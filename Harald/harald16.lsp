(defun x-coords (input-coords) (mapcar '(lambda (x) (nth 0 x)) input-coords))
(defun y-coords (input-coords) (mapcar '(lambda (x) (nth 1 x)) input-coords))
(defun remove-nil (in) (apply 'append (mapcar '(lambda (x) (if (not (null x)) (list x) ) ) in) ))
(defun get-coords (input-entity) (remove-nil (mapcar '(lambda (x) (if (= (car x) 10) (cdr x))) input-entity)))
(defun c:zoom-named (entname) (command "_zoom" "object" entname "")(princ))
(if (not (numberp (vl-string-search "Mac" (getvar "platform")))) (load "TXTEXP.LSP"))
;; NUMBER OF LAYERS: 16
; ERASE ALL
(command "_erase" "all" "")
; DRAW LAYERS, SET COLORS
(command "_layer" "new" "negYjunc" "")
(command "_layer" "new" "nitride" "")
(command "_layer" "new" "slices" "")
(command "_layer" "new" "holes" "")
(command "_layer" "new" "vgroove" "")
(command "_layer" "new" "vgrooveFDA" "")
(command "_layer" "new" "window" "")
(command "_layer" "new" "marks" "")
(command "_layer" "new" "extent" "")
(command "_layer" "new" "cover" "")
(command "_layer" "new" "grid" "")
(command "_layer" "new" "pads" "")
(command "_layer" "new" "text" "")
(command "_layer" "new" "fda1" "")
(command "_layer" "new" "prebias" "")
(command "_layer" "new" "phc" "")
(command "_layer" "new" "phccover" "")
(command "_layer" "new" "tethers" "")
(command "_layer" "new" "indicators" "")
(command "_layer" "new" "regionLayer1" "")
(command "_layer" "new" "regionLayer2" "")
(command "_layer" "new" "regionLayer3" "")
(command "_layer" "new" "regionLayer4" "")
(command "_layer" "new" "regionLayer5" "")
(command "_layer" "new" "regionLayer6" "")
(command "_layer" "new" "regionLayer7" "")
(command "_layer" "new" "regionLayer8" "")
(command "_layer" "new" "regionLayer9" "")
(command "_layer" "new" "regionLayer10" "")
(command "_layer" "new" "regionLayer11" "")
(command "_layer" "new" "regionLayer12" "")
(command "_layer" "new" "regionLayer13" "")
(command "_layer" "new" "regionLayer14" "")
(command "_layer" "new" "regionLayer15" "")
(command "_layer" "new" "regionLayer16" "")
(command "_layer" "color" "green" "negYjunc" "")
(command "_layer" "color" "white" "nitride" "")
(command "_layer" "color" "red" "slices" "")
(command "_layer" "color" "blue" "holes" "")
(command "_layer" "color" "green" "vgroove" "")
(command "_layer" "color" "red" "vgrooveFDA" "")
(command "_layer" "color" "yellow" "window" "")
(command "_layer" "color" "yellow" "marks" "")
(command "_layer" "color" "yellow" "extent" "")
(command "_layer" "color" "yellow" "cover" "")
(command "_layer" "color" "176" "grid" "")
(command "_layer" "color" "red" "pads" "")
(command "_layer" "color" "white" "text" "")
(command "_layer" "color" "1" "fda1" "")
(command "_layer" "color" "6" "prebias" "")
(command "_layer" "color" "5" "phc" "")
(command "_layer" "set" "negYjunc" "")
(command "_zoom" (list -0.05 -0.05) (list 0.05 0.05))
(command "_purge" "B" "*" "N")
; DEVICE #1
(command "_layer" "set" "window" "")
(command "_circle" "232.915,-415" "5")
(command "_layer" "set" "nitride" "")
(setq currobj nil)
(setq currobj (ssadd))
; DRAWING COUPLER
(setq coords (list 
(list 320.0645 -415) 
(list 320.0645 -413) 
(list 393.585 -413) 
(list 393.585 -413) 
(list 393.9677 -413.0761) 
(list 394.2921 -413.2929) 
(list 394.5089 -413.6173) 
(list 394.585 -414) 
(list 394.585 -411.8) 
(list 394.585 -411.8) 
(list 394.5089 -412.1827) 
(list 394.2921 -412.5071) 
(list 393.9677 -412.7239) 
(list 393.585 -412.8) 
(list 320.0645 -412.8) 
(list 320.0645 -410.8) 
(list 319.9355 -410.8) 
(list 319.9355 -412.8) 
(list 246.415 -412.8) 
(list 246.0323 -412.7239) 
(list 245.7079 -412.5071) 
(list 245.4911 -412.1827) 
(list 245.415 -411.8) 
(list 245.415 -411.8) 
(list 245.415 -414) 
(list 245.4911 -413.6173) 
(list 245.7079 -413.2929) 
(list 246.0323 -413.0761) 
(list 246.415 -413) 
(list 246.415 -413) 
(list 319.9355 -413) 
(list 319.9355 -415)))
(apply 'command (append '("pline") coords '("c")))
(setq currobj (ssadd (entlast) currobj))
(command "._fillet" "radius" "0.3" "._fillet" "P" (entlast))
(command "_layer" "set" "holes" "")
(command "_circle" "320,-412.9" "0.113")
(setq currobj (ssadd (entlast) currobj))
(command "_layer" "set" "nitride" "")
(command "_layer" "set" "text" "")
(command "_circle" "319.2,-415" "0.075")
(command "_circle" "319.2,-414.7" "0.075")
(command "_circle" "319.2,-414.4" "0.075")
(command "_circle" "318.9,-415" "0.075")
(command "_circle" "318.9,-414.7" "0.075")
(command "_circle" "318.9,-414.4" "0.075")
(command "_circle" "318.6,-415" "0.075")
(command "_circle" "318.6,-414.7" "0.075")
(command "_circle" "318.6,-414.4" "0.075")
(command "_layer" "set" "nitride" "")
(command "_layer" "set" "prebias" "")
(command "_rectangle" "245.415,-414" "394.585,-411.8")
(setq currobj (ssadd (entlast) currobj))
(command "_rectangle" "319.9355,-415" "320.0645,-410.8")
(setq currobj (ssadd (entlast) currobj))
(command "_layer" "set" "nitride" "")
(setq coupler1 currobj)
(setq currobj nil)
(setq currobj (ssadd))
; DRAWING SINGLE NANOBEAM
(setq coords (list 
(list 320.0645 -410.8) 
(list 320.0645 -409.1417) 
(list 320.0645 -407.4833) 
(list 320.0645 -405.825) 
(list 320.0645 -404.1667) 
(list 320.0645 -402.5083) 
(list 320.0645 -400.85) 
(list 320.0645 -399.1917) 
(list 320.0645 -397.5333) 
(list 320.0646 -395.875) 
(list 320.0646 -394.2167) 
(list 320.0646 -392.5583) 
(list 320.0646 -390.9) 
(list 320.0647 -389.2417) 
(list 320.0647 -387.5833) 
(list 320.0647 -385.925) 
(list 320.0648 -384.2667) 
(list 320.0648 -382.6083) 
(list 320.0649 -380.95) 
(list 320.065 -379.2917) 
(list 320.0651 -377.6333) 
(list 320.0651 -375.975) 
(list 320.0652 -374.3167) 
(list 320.0653 -372.6583) 
(list 320.0655 -371) 
(list 320.0656 -369.3417) 
(list 320.0657 -367.6833) 
(list 320.0659 -366.025) 
(list 320.066 -364.3667) 
(list 320.0662 -362.7083) 
(list 320.0664 -361.05) 
(list 320.0666 -359.3917) 
(list 320.0668 -357.7333) 
(list 320.067 -356.075) 
(list 320.0672 -354.4167) 
(list 320.0675 -352.7583) 
(list 320.0678 -351.1) 
(list 320.068 -349.4417) 
(list 320.0683 -347.7833) 
(list 320.0686 -346.125) 
(list 320.069 -344.4667) 
(list 320.0693 -342.8083) 
(list 320.0697 -341.15) 
(list 320.07 -339.4917) 
(list 320.0704 -337.8333) 
(list 320.0709 -336.175) 
(list 320.0713 -334.5167) 
(list 320.0717 -332.8583) 
(list 320.0722 -331.2) 
(list 320.0727 -329.5417) 
(list 320.0732 -327.8833) 
(list 320.0738 -326.225) 
(list 320.0743 -324.5667) 
(list 320.0749 -322.9083) 
(list 320.0755 -321.25) 
(list 320.0761 -319.5917) 
(list 320.0767 -317.9333) 
(list 320.0774 -316.275) 
(list 320.0781 -314.6167) 
(list 320.0788 -312.9583) 
(list 320.0796 -311.3) 
(list 320.0803 -309.6417) 
(list 320.0811 -307.9833) 
(list 320.0819 -306.325) 
(list 320.0828 -304.6667) 
(list 320.0837 -303.0083) 
(list 320.0845 -301.35) 
(list 320.0855 -299.6917) 
(list 320.0864 -298.0333) 
(list 320.0874 -296.375) 
(list 320.0884 -294.7167) 
(list 320.0895 -293.0583) 
(list 320.0905 -291.4) 
(list 320.0916 -289.7417) 
(list 320.0928 -288.0833) 
(list 320.0939 -286.425) 
(list 320.0951 -284.7667) 
(list 320.0963 -283.1083) 
(list 320.0976 -281.45) 
(list 320.0989 -279.7917) 
(list 320.1002 -278.1333) 
(list 320.1016 -276.475) 
(list 320.1029 -274.8167) 
(list 320.1044 -273.1583) 
(list 320.1058 -271.5) 
(list 320.1073 -269.8417) 
(list 320.1089 -268.1833) 
(list 320.1104 -266.525) 
(list 320.112 -264.8667) 
(list 320.1137 -263.2083) 
(list 320.1153 -261.55) 
(list 320.117 -259.8917) 
(list 320.1188 -258.2333) 
(list 320.1206 -256.575) 
(list 320.1224 -254.9167) 
(list 320.1243 -253.2583) 
(list 320.1262 -251.6) 
(list 320.1281 -249.9417) 
(list 320.1301 -248.2833) 
(list 320.1322 -246.625) 
(list 320.1342 -244.9667) 
(list 320.1363 -243.3083) 
(list 320.1385 -241.65) 
(list 320.1407 -239.9917) 
(list 320.1429 -238.3333) 
(list 320.1452 -236.675) 
(list 320.1476 -235.0167) 
(list 320.1499 -233.3583) 
(list 320.1523 -231.7) 
(list 320.1548 -230.0417) 
(list 320.1573 -228.3833) 
(list 320.1599 -226.725) 
(list 320.1625 -225.0667) 
(list 320.1651 -223.4083) 
(list 320.1678 -221.75) 
(list 320.1706 -220.0917) 
(list 320.1733 -218.4333) 
(list 320.1762 -216.775) 
(list 320.1791 -215.1167) 
(list 320.182 -213.4583) 
(list 320.185 -211.8) 
(list 319.815 -211.8) 
(list 319.818 -213.4583) 
(list 319.8209 -215.1167) 
(list 319.8238 -216.775) 
(list 319.8267 -218.4333) 
(list 319.8294 -220.0917) 
(list 319.8322 -221.75) 
(list 319.8349 -223.4083) 
(list 319.8375 -225.0667) 
(list 319.8401 -226.725) 
(list 319.8427 -228.3833) 
(list 319.8452 -230.0417) 
(list 319.8477 -231.7) 
(list 319.8501 -233.3583) 
(list 319.8524 -235.0167) 
(list 319.8548 -236.675) 
(list 319.8571 -238.3333) 
(list 319.8593 -239.9917) 
(list 319.8615 -241.65) 
(list 319.8637 -243.3083) 
(list 319.8658 -244.9667) 
(list 319.8678 -246.625) 
(list 319.8699 -248.2833) 
(list 319.8719 -249.9417) 
(list 319.8738 -251.6) 
(list 319.8757 -253.2583) 
(list 319.8776 -254.9167) 
(list 319.8794 -256.575) 
(list 319.8812 -258.2333) 
(list 319.883 -259.8917) 
(list 319.8847 -261.55) 
(list 319.8863 -263.2083) 
(list 319.888 -264.8667) 
(list 319.8896 -266.525) 
(list 319.8911 -268.1833) 
(list 319.8927 -269.8417) 
(list 319.8942 -271.5) 
(list 319.8956 -273.1583) 
(list 319.8971 -274.8167) 
(list 319.8984 -276.475) 
(list 319.8998 -278.1333) 
(list 319.9011 -279.7917) 
(list 319.9024 -281.45) 
(list 319.9037 -283.1083) 
(list 319.9049 -284.7667) 
(list 319.9061 -286.425) 
(list 319.9072 -288.0833) 
(list 319.9084 -289.7417) 
(list 319.9095 -291.4) 
(list 319.9105 -293.0583) 
(list 319.9116 -294.7167) 
(list 319.9126 -296.375) 
(list 319.9136 -298.0333) 
(list 319.9145 -299.6917) 
(list 319.9155 -301.35) 
(list 319.9163 -303.0083) 
(list 319.9172 -304.6667) 
(list 319.9181 -306.325) 
(list 319.9189 -307.9833) 
(list 319.9197 -309.6417) 
(list 319.9204 -311.3) 
(list 319.9212 -312.9583) 
(list 319.9219 -314.6167) 
(list 319.9226 -316.275) 
(list 319.9233 -317.9333) 
(list 319.9239 -319.5917) 
(list 319.9245 -321.25) 
(list 319.9251 -322.9083) 
(list 319.9257 -324.5667) 
(list 319.9262 -326.225) 
(list 319.9268 -327.8833) 
(list 319.9273 -329.5417) 
(list 319.9278 -331.2) 
(list 319.9283 -332.8583) 
(list 319.9287 -334.5167) 
(list 319.9291 -336.175) 
(list 319.9296 -337.8333) 
(list 319.93 -339.4917) 
(list 319.9303 -341.15) 
(list 319.9307 -342.8083) 
(list 319.931 -344.4667) 
(list 319.9314 -346.125) 
(list 319.9317 -347.7833) 
(list 319.932 -349.4417) 
(list 319.9322 -351.1) 
(list 319.9325 -352.7583) 
(list 319.9328 -354.4167) 
(list 319.933 -356.075) 
(list 319.9332 -357.7333) 
(list 319.9334 -359.3917) 
(list 319.9336 -361.05) 
(list 319.9338 -362.7083) 
(list 319.934 -364.3667) 
(list 319.9341 -366.025) 
(list 319.9343 -367.6833) 
(list 319.9344 -369.3417) 
(list 319.9345 -371) 
(list 319.9347 -372.6583) 
(list 319.9348 -374.3167) 
(list 319.9349 -375.975) 
(list 319.9349 -377.6333) 
(list 319.935 -379.2917) 
(list 319.9351 -380.95) 
(list 319.9352 -382.6083) 
(list 319.9352 -384.2667) 
(list 319.9353 -385.925) 
(list 319.9353 -387.5833) 
(list 319.9353 -389.2417) 
(list 319.9354 -390.9) 
(list 319.9354 -392.5583) 
(list 319.9354 -394.2167) 
(list 319.9354 -395.875) 
(list 319.9355 -397.5333) 
(list 319.9355 -399.1917) 
(list 319.9355 -400.85) 
(list 319.9355 -402.5083) 
(list 319.9355 -404.1667) 
(list 319.9355 -405.825) 
(list 319.9355 -407.4833) 
(list 319.9355 -409.1417) 
(list 319.9355 -410.8)))
(apply 'command (append '("pline") coords '("c")))
(setq currobj (ssadd (entlast) currobj))
(command "_layer" "set" "prebias" "")
(command "_rectangle" "319.815,-410.8" "320.185,-211.8")
(setq currobj (ssadd (entlast) currobj))
(command "_layer" "set" "nitride" "")
(setq singlenanobeam1 currobj)
(setq currobj nil)
(setq currobj (ssadd))
; DRAWING NODE ARRAY
(setq coords (list 
(list 320.185 -211.8) 
(list 320.5625 -201.8) 
(list 320.5625 -201.8) 
(list 320.5625 -200.8) 
(list 394.585 -212.6864) 
(list 394.585 -207.7434) 
(list 320.5625 -197.357) 
(list 320.5625 -196.357) 
(list 320.5625 -196.357) 
(list 320.2625 -186.357) 
(list 319.7375 -186.357) 
(list 319.4375 -196.357) 
(list 319.4375 -196.357) 
(list 319.4375 -197.357) 
(list 245.415 -207.7434) 
(list 245.415 -212.6864) 
(list 319.4375 -200.8) 
(list 319.4375 -201.8) 
(list 319.4375 -201.8) 
(list 319.815 -211.8)))
(apply 'command (append '("pline") coords '("c")))
(setq currobj (ssadd (entlast) currobj))
(command "_layer" "set" "prebias" "")
(setq coords (list 
(list 319.4375 -212.6864) 
(list 319.4375 -200.8) 
(list 245.415 -212.6864) 
(list 245.415 -207.7434) 
(list 319.4375 -197.357) 
(list 319.4375 -186.357) 
(list 320.5625 -186.357) 
(list 320.5625 -197.357) 
(list 394.585 -207.7434) 
(list 394.585 -212.6864) 
(list 320.5625 -200.8) 
(list 320.5625 -212.6864)))
(apply 'command (append '("pline") coords '("c")))
(setq currobj (ssadd (entlast) currobj))
(command "_layer" "set" "nitride" "")
(command "_layer" "set" "fda1" "")
(setq coords (list 
(list 320.5625 -200.657) 
(list 394.585 -212.5434) 
(list 394.585 -212.3664) 
(list 320.5625 -200.58)))
(apply 'command (append '("pline") coords '("c")))
(setq currobj (ssadd (entlast) currobj))
(setq coords (list 
(list 320.5625 -200.437) 
(list 394.585 -212.2234) 
(list 394.585 -212.0464) 
(list 320.5625 -200.36)))
(apply 'command (append '("pline") coords '("c")))
(setq currobj (ssadd (entlast) currobj))
(setq coords (list 
(list 320.5625 -200.217) 
(list 394.585 -211.9034) 
(list 394.585 -211.7264) 
(list 320.5625 -200.14)))
(apply 'command (append '("pline") coords '("c")))
(setq currobj (ssadd (entlast) currobj))
(setq coords (list 
(list 320.5625 -199.997) 
(list 394.585 -211.5834) 
(list 394.585 -211.4064) 
(list 320.5625 -199.92)))
(apply 'command (append '("pline") coords '("c")))
(setq currobj (ssadd (entlast) currobj))
(setq coords (list 
(list 320.5625 -199.777) 
(list 394.585 -211.2634) 
(list 394.585 -211.0864) 
(list 320.5625 -199.7)))
(apply 'command (append '("pline") coords '("c")))
(setq currobj (ssadd (entlast) currobj))
(setq coords (list 
(list 320.5625 -199.557) 
(list 394.585 -210.9434) 
(list 394.585 -210.7664) 
(list 320.5625 -199.48)))
(apply 'command (append '("pline") coords '("c")))
(setq currobj (ssadd (entlast) currobj))
(setq coords (list 
(list 320.5625 -199.337) 
(list 394.585 -210.6234) 
(list 394.585 -210.4464) 
(list 320.5625 -199.26)))
(apply 'command (append '("pline") coords '("c")))
(setq currobj (ssadd (entlast) currobj))
(setq coords (list 
(list 320.5625 -199.117) 
(list 394.585 -210.3034) 
(list 394.585 -210.1264) 
(list 320.5625 -199.04)))
(apply 'command (append '("pline") coords '("c")))
(setq currobj (ssadd (entlast) currobj))
(setq coords (list 
(list 320.5625 -198.897) 
(list 394.585 -209.9834) 
(list 394.585 -209.8064) 
(list 320.5625 -198.82)))
(apply 'command (append '("pline") coords '("c")))
(setq currobj (ssadd (entlast) currobj))
(setq coords (list 
(list 320.5625 -198.677) 
(list 394.585 -209.6634) 
(list 394.585 -209.4864) 
(list 320.5625 -198.6)))
(apply 'command (append '("pline") coords '("c")))
(setq currobj (ssadd (entlast) currobj))
(setq coords (list 
(list 320.5625 -198.457) 
(list 394.585 -209.3434) 
(list 394.585 -209.1664) 
(list 320.5625 -198.38)))
(apply 'command (append '("pline") coords '("c")))
(setq currobj (ssadd (entlast) currobj))
(setq coords (list 
(list 320.5625 -198.237) 
(list 394.585 -209.0234) 
(list 394.585 -208.8464) 
(list 320.5625 -198.16)))
(apply 'command (append '("pline") coords '("c")))
(setq currobj (ssadd (entlast) currobj))
(setq coords (list 
(list 320.5625 -198.017) 
(list 394.585 -208.7034) 
(list 394.585 -208.5264) 
(list 320.5625 -197.94)))
(apply 'command (append '("pline") coords '("c")))
(setq currobj (ssadd (entlast) currobj))
(setq coords (list 
(list 320.5625 -197.797) 
(list 394.585 -208.3834) 
(list 394.585 -208.2064) 
(list 320.5625 -197.72)))
(apply 'command (append '("pline") coords '("c")))
(setq currobj (ssadd (entlast) currobj))
(setq coords (list 
(list 320.5625 -197.577) 
(list 394.585 -208.0634) 
(list 394.585 -207.8864) 
(list 320.5625 -197.5)))
(apply 'command (append '("pline") coords '("c")))
(setq currobj (ssadd (entlast) currobj))
(setq coords (list 
(list 319.4375 -197.5) 
(list 245.415 -207.8864) 
(list 245.415 -208.0634) 
(list 319.4375 -197.577)))
(apply 'command (append '("pline") coords '("c")))
(setq currobj (ssadd (entlast) currobj))
(setq coords (list 
(list 319.4375 -197.72) 
(list 245.415 -208.2064) 
(list 245.415 -208.3834) 
(list 319.4375 -197.797)))
(apply 'command (append '("pline") coords '("c")))
(setq currobj (ssadd (entlast) currobj))
(setq coords (list 
(list 319.4375 -197.94) 
(list 245.415 -208.5264) 
(list 245.415 -208.7034) 
(list 319.4375 -198.017)))
(apply 'command (append '("pline") coords '("c")))
(setq currobj (ssadd (entlast) currobj))
(setq coords (list 
(list 319.4375 -198.16) 
(list 245.415 -208.8464) 
(list 245.415 -209.0234) 
(list 319.4375 -198.237)))
(apply 'command (append '("pline") coords '("c")))
(setq currobj (ssadd (entlast) currobj))
(setq coords (list 
(list 319.4375 -198.38) 
(list 245.415 -209.1664) 
(list 245.415 -209.3434) 
(list 319.4375 -198.457)))
(apply 'command (append '("pline") coords '("c")))
(setq currobj (ssadd (entlast) currobj))
(setq coords (list 
(list 319.4375 -198.6) 
(list 245.415 -209.4864) 
(list 245.415 -209.6634) 
(list 319.4375 -198.677)))
(apply 'command (append '("pline") coords '("c")))
(setq currobj (ssadd (entlast) currobj))
(setq coords (list 
(list 319.4375 -198.82) 
(list 245.415 -209.8064) 
(list 245.415 -209.9834) 
(list 319.4375 -198.897)))
(apply 'command (append '("pline") coords '("c")))
(setq currobj (ssadd (entlast) currobj))
(setq coords (list 
(list 319.4375 -199.04) 
(list 245.415 -210.1264) 
(list 245.415 -210.3034) 
(list 319.4375 -199.117)))
(apply 'command (append '("pline") coords '("c")))
(setq currobj (ssadd (entlast) currobj))
(setq coords (list 
(list 319.4375 -199.26) 
(list 245.415 -210.4464) 
(list 245.415 -210.6234) 
(list 319.4375 -199.337)))
(apply 'command (append '("pline") coords '("c")))
(setq currobj (ssadd (entlast) currobj))
(setq coords (list 
(list 319.4375 -199.48) 
(list 245.415 -210.7664) 
(list 245.415 -210.9434) 
(list 319.4375 -199.557)))
(apply 'command (append '("pline") coords '("c")))
(setq currobj (ssadd (entlast) currobj))
(setq coords (list 
(list 319.4375 -199.7) 
(list 245.415 -211.0864) 
(list 245.415 -211.2634) 
(list 319.4375 -199.777)))
(apply 'command (append '("pline") coords '("c")))
(setq currobj (ssadd (entlast) currobj))
(setq coords (list 
(list 319.4375 -199.92) 
(list 245.415 -211.4064) 
(list 245.415 -211.5834) 
(list 319.4375 -199.997)))
(apply 'command (append '("pline") coords '("c")))
(setq currobj (ssadd (entlast) currobj))
(setq coords (list 
(list 319.4375 -200.14) 
(list 245.415 -211.7264) 
(list 245.415 -211.9034) 
(list 319.4375 -200.217)))
(apply 'command (append '("pline") coords '("c")))
(setq currobj (ssadd (entlast) currobj))
(setq coords (list 
(list 319.4375 -200.36) 
(list 245.415 -212.0464) 
(list 245.415 -212.2234) 
(list 319.4375 -200.437)))
(apply 'command (append '("pline") coords '("c")))
(setq currobj (ssadd (entlast) currobj))
(setq coords (list 
(list 319.4375 -200.58) 
(list 245.415 -212.3664) 
(list 245.415 -212.5434) 
(list 319.4375 -200.657)))
(apply 'command (append '("pline") coords '("c")))
(setq currobj (ssadd (entlast) currobj))
(command "_layer" "set" "nitride" "")
(command "_layer" "set" "text" "")
(command "_circle" "318.985,-211.8" "0.075")
(command "_circle" "318.985,-211.5" "0.075")
(command "_circle" "318.985,-211.2" "0.075")
(command "_circle" "318.985,-210.9" "0.075")
(command "_circle" "318.985,-210.6" "0.075")
(command "_circle" "318.685,-211.8" "0.075")
(command "_circle" "318.685,-211.5" "0.075")
(command "_circle" "318.685,-211.2" "0.075")
(command "_circle" "318.685,-210.9" "0.075")
(command "_circle" "318.685,-210.6" "0.075")
(command "_circle" "318.385,-211.8" "0.075")
(command "_circle" "318.385,-211.5" "0.075")
(command "_circle" "318.385,-211.2" "0.075")
(command "_circle" "318.385,-210.9" "0.075")
(command "_circle" "318.385,-210.6" "0.075")
(command "_circle" "318.085,-211.8" "0.075")
(command "_circle" "318.085,-211.5" "0.075")
(command "_circle" "318.085,-211.2" "0.075")
(command "_circle" "318.085,-210.9" "0.075")
(command "_circle" "318.085,-210.6" "0.075")
(command "_circle" "317.785,-211.8" "0.075")
(command "_circle" "317.785,-211.5" "0.075")
(command "_circle" "317.785,-211.2" "0.075")
(command "_circle" "317.785,-210.9" "0.075")
(command "_circle" "317.785,-210.6" "0.075")
(command "_layer" "set" "nitride" "")
(setq anglednodearray1 currobj)
(setq currobj nil)
(setq currobj (ssadd))
; DRAWING COOLED SINGLE NANOBEAM
(setq coords (list 
(list 320.2625 -186.357) 
(list 320.2625 -181.357) 
(list 319.7375 -181.357) 
(list 319.7375 -186.357)))
(apply 'command (append '("pline") coords '("c")))
(setq currobj (ssadd (entlast) currobj))
(command "_layer" "set" "prebias" "")
(command "_rectangle" "319.7375,-186.357" "320.2625,-181.357")
(setq currobj (ssadd (entlast) currobj))
(command "_layer" "set" "nitride" "")
(setq coords (list 
(list 320.2625 -181.357) 
(list 320.5625 -171.357) 
(list 320.5625 -171.357) 
(list 320.5625 -170.357) 
(list 394.585 -171.107) 
(list 394.585 -166.164) 
(list 320.5625 -166.914) 
(list 320.5625 -165.914) 
(list 320.5625 -165.914) 
(list 320.2625 -155.914) 
(list 319.7375 -155.914) 
(list 319.4375 -165.914) 
(list 319.4375 -165.914) 
(list 319.4375 -166.914) 
(list 245.415 -166.164) 
(list 245.415 -171.107) 
(list 319.4375 -170.357) 
(list 319.4375 -171.357) 
(list 319.4375 -171.357) 
(list 319.7375 -181.357)))
(apply 'command (append '("pline") coords '("c")))
(setq currobj (ssadd (entlast) currobj))
(command "_layer" "set" "prebias" "")
(setq coords (list 
(list 319.4375 -181.357) 
(list 319.4375 -170.357) 
(list 245.415 -171.107) 
(list 245.415 -166.164) 
(list 319.4375 -166.914) 
(list 319.4375 -155.914) 
(list 320.5625 -155.914) 
(list 320.5625 -166.914) 
(list 394.585 -166.164) 
(list 394.585 -171.107) 
(list 320.5625 -170.357) 
(list 320.5625 -181.357)))
(apply 'command (append '("pline") coords '("c")))
(setq currobj (ssadd (entlast) currobj))
(command "_layer" "set" "nitride" "")
(command "_layer" "set" "fda1" "")
(setq coords (list 
(list 320.5625 -170.214) 
(list 394.585 -170.964) 
(list 394.585 -170.787) 
(list 320.5625 -170.137)))
(apply 'command (append '("pline") coords '("c")))
(setq currobj (ssadd (entlast) currobj))
(setq coords (list 
(list 320.5625 -169.994) 
(list 394.585 -170.644) 
(list 394.585 -170.467) 
(list 320.5625 -169.917)))
(apply 'command (append '("pline") coords '("c")))
(setq currobj (ssadd (entlast) currobj))
(setq coords (list 
(list 320.5625 -169.774) 
(list 394.585 -170.324) 
(list 394.585 -170.147) 
(list 320.5625 -169.697)))
(apply 'command (append '("pline") coords '("c")))
(setq currobj (ssadd (entlast) currobj))
(setq coords (list 
(list 320.5625 -169.554) 
(list 394.585 -170.004) 
(list 394.585 -169.827) 
(list 320.5625 -169.477)))
(apply 'command (append '("pline") coords '("c")))
(setq currobj (ssadd (entlast) currobj))
(setq coords (list 
(list 320.5625 -169.334) 
(list 394.585 -169.684) 
(list 394.585 -169.507) 
(list 320.5625 -169.257)))
(apply 'command (append '("pline") coords '("c")))
(setq currobj (ssadd (entlast) currobj))
(setq coords (list 
(list 320.5625 -169.114) 
(list 394.585 -169.364) 
(list 394.585 -169.187) 
(list 320.5625 -169.037)))
(apply 'command (append '("pline") coords '("c")))
(setq currobj (ssadd (entlast) currobj))
(setq coords (list 
(list 320.5625 -168.894) 
(list 394.585 -169.044) 
(list 394.585 -168.867) 
(list 320.5625 -168.817)))
(apply 'command (append '("pline") coords '("c")))
(setq currobj (ssadd (entlast) currobj))
(setq coords (list 
(list 320.5625 -168.674) 
(list 394.585 -168.724) 
(list 394.585 -168.547) 
(list 320.5625 -168.597)))
(apply 'command (append '("pline") coords '("c")))
(setq currobj (ssadd (entlast) currobj))
(setq coords (list 
(list 320.5625 -168.454) 
(list 394.585 -168.404) 
(list 394.585 -168.227) 
(list 320.5625 -168.377)))
(apply 'command (append '("pline") coords '("c")))
(setq currobj (ssadd (entlast) currobj))
(setq coords (list 
(list 320.5625 -168.234) 
(list 394.585 -168.084) 
(list 394.585 -167.907) 
(list 320.5625 -168.157)))
(apply 'command (append '("pline") coords '("c")))
(setq currobj (ssadd (entlast) currobj))
(setq coords (list 
(list 320.5625 -168.014) 
(list 394.585 -167.764) 
(list 394.585 -167.587) 
(list 320.5625 -167.937)))
(apply 'command (append '("pline") coords '("c")))
(setq currobj (ssadd (entlast) currobj))
(setq coords (list 
(list 320.5625 -167.794) 
(list 394.585 -167.444) 
(list 394.585 -167.267) 
(list 320.5625 -167.717)))
(apply 'command (append '("pline") coords '("c")))
(setq currobj (ssadd (entlast) currobj))
(setq coords (list 
(list 320.5625 -167.574) 
(list 394.585 -167.124) 
(list 394.585 -166.947) 
(list 320.5625 -167.497)))
(apply 'command (append '("pline") coords '("c")))
(setq currobj (ssadd (entlast) currobj))
(setq coords (list 
(list 320.5625 -167.354) 
(list 394.585 -166.804) 
(list 394.585 -166.627) 
(list 320.5625 -167.277)))
(apply 'command (append '("pline") coords '("c")))
(setq currobj (ssadd (entlast) currobj))
(setq coords (list 
(list 320.5625 -167.134) 
(list 394.585 -166.484) 
(list 394.585 -166.307) 
(list 320.5625 -167.057)))
(apply 'command (append '("pline") coords '("c")))
(setq currobj (ssadd (entlast) currobj))
(setq coords (list 
(list 319.4375 -167.057) 
(list 245.415 -166.307) 
(list 245.415 -166.484) 
(list 319.4375 -167.134)))
(apply 'command (append '("pline") coords '("c")))
(setq currobj (ssadd (entlast) currobj))
(setq coords (list 
(list 319.4375 -167.277) 
(list 245.415 -166.627) 
(list 245.415 -166.804) 
(list 319.4375 -167.354)))
(apply 'command (append '("pline") coords '("c")))
(setq currobj (ssadd (entlast) currobj))
(setq coords (list 
(list 319.4375 -167.497) 
(list 245.415 -166.947) 
(list 245.415 -167.124) 
(list 319.4375 -167.574)))
(apply 'command (append '("pline") coords '("c")))
(setq currobj (ssadd (entlast) currobj))
(setq coords (list 
(list 319.4375 -167.717) 
(list 245.415 -167.267) 
(list 245.415 -167.444) 
(list 319.4375 -167.794)))
(apply 'command (append '("pline") coords '("c")))
(setq currobj (ssadd (entlast) currobj))
(setq coords (list 
(list 319.4375 -167.937) 
(list 245.415 -167.587) 
(list 245.415 -167.764) 
(list 319.4375 -168.014)))
(apply 'command (append '("pline") coords '("c")))
(setq currobj (ssadd (entlast) currobj))
(setq coords (list 
(list 319.4375 -168.157) 
(list 245.415 -167.907) 
(list 245.415 -168.084) 
(list 319.4375 -168.234)))
(apply 'command (append '("pline") coords '("c")))
(setq currobj (ssadd (entlast) currobj))
(setq coords (list 
(list 319.4375 -168.377) 
(list 245.415 -168.227) 
(list 245.415 -168.404) 
(list 319.4375 -168.454)))
(apply 'command (append '("pline") coords '("c")))
(setq currobj (ssadd (entlast) currobj))
(setq coords (list 
(list 319.4375 -168.597) 
(list 245.415 -168.547) 
(list 245.415 -168.724) 
(list 319.4375 -168.674)))
(apply 'command (append '("pline") coords '("c")))
(setq currobj (ssadd (entlast) currobj))
(setq coords (list 
(list 319.4375 -168.817) 
(list 245.415 -168.867) 
(list 245.415 -169.044) 
(list 319.4375 -168.894)))
(apply 'command (append '("pline") coords '("c")))
(setq currobj (ssadd (entlast) currobj))
(setq coords (list 
(list 319.4375 -169.037) 
(list 245.415 -169.187) 
(list 245.415 -169.364) 
(list 319.4375 -169.114)))
(apply 'command (append '("pline") coords '("c")))
(setq currobj (ssadd (entlast) currobj))
(setq coords (list 
(list 319.4375 -169.257) 
(list 245.415 -169.507) 
(list 245.415 -169.684) 
(list 319.4375 -169.334)))
(apply 'command (append '("pline") coords '("c")))
(setq currobj (ssadd (entlast) currobj))
(setq coords (list 
(list 319.4375 -169.477) 
(list 245.415 -169.827) 
(list 245.415 -170.004) 
(list 319.4375 -169.554)))
(apply 'command (append '("pline") coords '("c")))
(setq currobj (ssadd (entlast) currobj))
(setq coords (list 
(list 319.4375 -169.697) 
(list 245.415 -170.147) 
(list 245.415 -170.324) 
(list 319.4375 -169.774)))
(apply 'command (append '("pline") coords '("c")))
(setq currobj (ssadd (entlast) currobj))
(setq coords (list 
(list 319.4375 -169.917) 
(list 245.415 -170.467) 
(list 245.415 -170.644) 
(list 319.4375 -169.994)))
(apply 'command (append '("pline") coords '("c")))
(setq currobj (ssadd (entlast) currobj))
(setq coords (list 
(list 319.4375 -170.137) 
(list 245.415 -170.787) 
(list 245.415 -170.964) 
(list 319.4375 -170.214)))
(apply 'command (append '("pline") coords '("c")))
(setq currobj (ssadd (entlast) currobj))
(command "_layer" "set" "nitride" "")
(command "_layer" "set" "text" "")
(command "_circle" "319.0625,-181.357" "0.075")
(command "_circle" "319.0625,-181.057" "0.075")
(command "_circle" "319.0625,-180.757" "0.075")
(command "_circle" "319.0625,-180.457" "0.075")
(command "_circle" "319.0625,-180.157" "0.075")
(command "_circle" "318.7625,-181.357" "0.075")
(command "_circle" "318.7625,-181.057" "0.075")
(command "_circle" "318.7625,-180.757" "0.075")
(command "_circle" "318.7625,-180.457" "0.075")
(command "_circle" "318.7625,-180.157" "0.075")
(command "_circle" "318.4625,-181.357" "0.075")
(command "_circle" "318.4625,-181.057" "0.075")
(command "_circle" "318.4625,-180.757" "0.075")
(command "_circle" "318.4625,-180.457" "0.075")
(command "_circle" "318.4625,-180.157" "0.075")
(command "_circle" "318.1625,-181.357" "0.075")
(command "_circle" "318.1625,-181.057" "0.075")
(command "_circle" "318.1625,-180.757" "0.075")
(command "_circle" "318.1625,-180.457" "0.075")
(command "_circle" "318.1625,-180.157" "0.075")
(command "_circle" "317.8625,-181.357" "0.075")
(command "_circle" "317.8625,-181.057" "0.075")
(command "_circle" "317.8625,-180.757" "0.075")
(command "_circle" "317.8625,-180.457" "0.075")
(command "_circle" "317.8625,-180.157" "0.075")
(command "_layer" "set" "nitride" "")
(setq coords (list 
(list 320.2625 -155.914) 
(list 320.2625 -40.2693) 
(list 319.7375 -40.2693) 
(list 319.7375 -155.914)))
(apply 'command (append '("pline") coords '("c")))
(setq currobj (ssadd (entlast) currobj))
(command "_layer" "set" "prebias" "")
(command "_rectangle" "319.7375,-155.914" "320.2625,-40.2693")
(setq currobj (ssadd (entlast) currobj))
(command "_layer" "set" "nitride" "")
(setq coords (list 
(list 320.2625 -40.2693) 
(list 320.5625 -30.2693) 
(list 320.5625 -30.2693) 
(list 320.5625 -29.2693) 
(list 394.585 -30.0193) 
(list 394.585 -25.0763) 
(list 320.5625 -25.8263) 
(list 320.5625 -24.8263) 
(list 320.5625 -24.8263) 
(list 320.2625 -14.8263) 
(list 319.7375 -14.8263) 
(list 319.4375 -24.8263) 
(list 319.4375 -24.8263) 
(list 319.4375 -25.8263) 
(list 245.415 -25.0763) 
(list 245.415 -30.0193) 
(list 319.4375 -29.2693) 
(list 319.4375 -30.2693) 
(list 319.4375 -30.2693) 
(list 319.7375 -40.2693)))
(apply 'command (append '("pline") coords '("c")))
(setq currobj (ssadd (entlast) currobj))
(command "_layer" "set" "prebias" "")
(setq coords (list 
(list 319.4375 -40.2693) 
(list 319.4375 -29.2693) 
(list 245.415 -30.0193) 
(list 245.415 -25.0763) 
(list 319.4375 -25.8263) 
(list 319.4375 -14.8263) 
(list 320.5625 -14.8263) 
(list 320.5625 -25.8263) 
(list 394.585 -25.0763) 
(list 394.585 -30.0193) 
(list 320.5625 -29.2693) 
(list 320.5625 -40.2693)))
(apply 'command (append '("pline") coords '("c")))
(setq currobj (ssadd (entlast) currobj))
(command "_layer" "set" "nitride" "")
(command "_layer" "set" "fda1" "")
(setq coords (list 
(list 320.5625 -29.1263) 
(list 394.585 -29.8763) 
(list 394.585 -29.6993) 
(list 320.5625 -29.0493)))
(apply 'command (append '("pline") coords '("c")))
(setq currobj (ssadd (entlast) currobj))
(setq coords (list 
(list 320.5625 -28.9063) 
(list 394.585 -29.5563) 
(list 394.585 -29.3793) 
(list 320.5625 -28.8293)))
(apply 'command (append '("pline") coords '("c")))
(setq currobj (ssadd (entlast) currobj))
(setq coords (list 
(list 320.5625 -28.6863) 
(list 394.585 -29.2363) 
(list 394.585 -29.0593) 
(list 320.5625 -28.6093)))
(apply 'command (append '("pline") coords '("c")))
(setq currobj (ssadd (entlast) currobj))
(setq coords (list 
(list 320.5625 -28.4663) 
(list 394.585 -28.9163) 
(list 394.585 -28.7393) 
(list 320.5625 -28.3893)))
(apply 'command (append '("pline") coords '("c")))
(setq currobj (ssadd (entlast) currobj))
(setq coords (list 
(list 320.5625 -28.2463) 
(list 394.585 -28.5963) 
(list 394.585 -28.4193) 
(list 320.5625 -28.1693)))
(apply 'command (append '("pline") coords '("c")))
(setq currobj (ssadd (entlast) currobj))
(setq coords (list 
(list 320.5625 -28.0263) 
(list 394.585 -28.2763) 
(list 394.585 -28.0993) 
(list 320.5625 -27.9493)))
(apply 'command (append '("pline") coords '("c")))
(setq currobj (ssadd (entlast) currobj))
(setq coords (list 
(list 320.5625 -27.8063) 
(list 394.585 -27.9563) 
(list 394.585 -27.7793) 
(list 320.5625 -27.7293)))
(apply 'command (append '("pline") coords '("c")))
(setq currobj (ssadd (entlast) currobj))
(setq coords (list 
(list 320.5625 -27.5863) 
(list 394.585 -27.6363) 
(list 394.585 -27.4593) 
(list 320.5625 -27.5093)))
(apply 'command (append '("pline") coords '("c")))
(setq currobj (ssadd (entlast) currobj))
(setq coords (list 
(list 320.5625 -27.3663) 
(list 394.585 -27.3163) 
(list 394.585 -27.1393) 
(list 320.5625 -27.2893)))
(apply 'command (append '("pline") coords '("c")))
(setq currobj (ssadd (entlast) currobj))
(setq coords (list 
(list 320.5625 -27.1463) 
(list 394.585 -26.9963) 
(list 394.585 -26.8193) 
(list 320.5625 -27.0693)))
(apply 'command (append '("pline") coords '("c")))
(setq currobj (ssadd (entlast) currobj))
(setq coords (list 
(list 320.5625 -26.9263) 
(list 394.585 -26.6763) 
(list 394.585 -26.4993) 
(list 320.5625 -26.8493)))
(apply 'command (append '("pline") coords '("c")))
(setq currobj (ssadd (entlast) currobj))
(setq coords (list 
(list 320.5625 -26.7063) 
(list 394.585 -26.3563) 
(list 394.585 -26.1793) 
(list 320.5625 -26.6293)))
(apply 'command (append '("pline") coords '("c")))
(setq currobj (ssadd (entlast) currobj))
(setq coords (list 
(list 320.5625 -26.4863) 
(list 394.585 -26.0363) 
(list 394.585 -25.8593) 
(list 320.5625 -26.4093)))
(apply 'command (append '("pline") coords '("c")))
(setq currobj (ssadd (entlast) currobj))
(setq coords (list 
(list 320.5625 -26.2663) 
(list 394.585 -25.7163) 
(list 394.585 -25.5393) 
(list 320.5625 -26.1893)))
(apply 'command (append '("pline") coords '("c")))
(setq currobj (ssadd (entlast) currobj))
(setq coords (list 
(list 320.5625 -26.0463) 
(list 394.585 -25.3963) 
(list 394.585 -25.2193) 
(list 320.5625 -25.9693)))
(apply 'command (append '("pline") coords '("c")))
(setq currobj (ssadd (entlast) currobj))
(setq coords (list 
(list 319.4375 -25.9693) 
(list 245.415 -25.2193) 
(list 245.415 -25.3963) 
(list 319.4375 -26.0463)))
(apply 'command (append '("pline") coords '("c")))
(setq currobj (ssadd (entlast) currobj))
(setq coords (list 
(list 319.4375 -26.1893) 
(list 245.415 -25.5393) 
(list 245.415 -25.7163) 
(list 319.4375 -26.2663)))
(apply 'command (append '("pline") coords '("c")))
(setq currobj (ssadd (entlast) currobj))
(setq coords (list 
(list 319.4375 -26.4093) 
(list 245.415 -25.8593) 
(list 245.415 -26.0363) 
(list 319.4375 -26.4863)))
(apply 'command (append '("pline") coords '("c")))
(setq currobj (ssadd (entlast) currobj))
(setq coords (list 
(list 319.4375 -26.6293) 
(list 245.415 -26.1793) 
(list 245.415 -26.3563) 
(list 319.4375 -26.7063)))
(apply 'command (append '("pline") coords '("c")))
(setq currobj (ssadd (entlast) currobj))
(setq coords (list 
(list 319.4375 -26.8493) 
(list 245.415 -26.4993) 
(list 245.415 -26.6763) 
(list 319.4375 -26.9263)))
(apply 'command (append '("pline") coords '("c")))
(setq currobj (ssadd (entlast) currobj))
(setq coords (list 
(list 319.4375 -27.0693) 
(list 245.415 -26.8193) 
(list 245.415 -26.9963) 
(list 319.4375 -27.1463)))
(apply 'command (append '("pline") coords '("c")))
(setq currobj (ssadd (entlast) currobj))
(setq coords (list 
(list 319.4375 -27.2893) 
(list 245.415 -27.1393) 
(list 245.415 -27.3163) 
(list 319.4375 -27.3663)))
(apply 'command (append '("pline") coords '("c")))
(setq currobj (ssadd (entlast) currobj))
(setq coords (list 
(list 319.4375 -27.5093) 
(list 245.415 -27.4593) 
(list 245.415 -27.6363) 
(list 319.4375 -27.5863)))
(apply 'command (append '("pline") coords '("c")))
(setq currobj (ssadd (entlast) currobj))
(setq coords (list 
(list 319.4375 -27.7293) 
(list 245.415 -27.7793) 
(list 245.415 -27.9563) 
(list 319.4375 -27.8063)))
(apply 'command (append '("pline") coords '("c")))
(setq currobj (ssadd (entlast) currobj))
(setq coords (list 
(list 319.4375 -27.9493) 
(list 245.415 -28.0993) 
(list 245.415 -28.2763) 
(list 319.4375 -28.0263)))
(apply 'command (append '("pline") coords '("c")))
(setq currobj (ssadd (entlast) currobj))
(setq coords (list 
(list 319.4375 -28.1693) 
(list 245.415 -28.4193) 
(list 245.415 -28.5963) 
(list 319.4375 -28.2463)))
(apply 'command (append '("pline") coords '("c")))
(setq currobj (ssadd (entlast) currobj))
(setq coords (list 
(list 319.4375 -28.3893) 
(list 245.415 -28.7393) 
(list 245.415 -28.9163) 
(list 319.4375 -28.4663)))
(apply 'command (append '("pline") coords '("c")))
(setq currobj (ssadd (entlast) currobj))
(setq coords (list 
(list 319.4375 -28.6093) 
(list 245.415 -29.0593) 
(list 245.415 -29.2363) 
(list 319.4375 -28.6863)))
(apply 'command (append '("pline") coords '("c")))
(setq currobj (ssadd (entlast) currobj))
(setq coords (list 
(list 319.4375 -28.8293) 
(list 245.415 -29.3793) 
(list 245.415 -29.5563) 
(list 319.4375 -28.9063)))
(apply 'command (append '("pline") coords '("c")))
(setq currobj (ssadd (entlast) currobj))
(setq coords (list 
(list 319.4375 -29.0493) 
(list 245.415 -29.6993) 
(list 245.415 -29.8763) 
(list 319.4375 -29.1263)))
(apply 'command (append '("pline") coords '("c")))
(setq currobj (ssadd (entlast) currobj))
(command "_layer" "set" "nitride" "")
(command "_layer" "set" "text" "")
(command "_circle" "319.0625,-40.2693" "0.075")
(command "_circle" "319.0625,-39.9693" "0.075")
(command "_circle" "319.0625,-39.6693" "0.075")
(command "_circle" "319.0625,-39.3693" "0.075")
(command "_circle" "319.0625,-39.0693" "0.075")
(command "_circle" "318.7625,-40.2693" "0.075")
(command "_circle" "318.7625,-39.9693" "0.075")
(command "_circle" "318.7625,-39.6693" "0.075")
(command "_circle" "318.7625,-39.3693" "0.075")
(command "_circle" "318.7625,-39.0693" "0.075")
(command "_circle" "318.4625,-40.2693" "0.075")
(command "_circle" "318.4625,-39.9693" "0.075")
(command "_circle" "318.4625,-39.6693" "0.075")
(command "_circle" "318.4625,-39.3693" "0.075")
(command "_circle" "318.4625,-39.0693" "0.075")
(command "_circle" "318.1625,-40.2693" "0.075")
(command "_circle" "318.1625,-39.9693" "0.075")
(command "_circle" "318.1625,-39.6693" "0.075")
(command "_circle" "318.1625,-39.3693" "0.075")
(command "_circle" "318.1625,-39.0693" "0.075")
(command "_circle" "317.8625,-40.2693" "0.075")
(command "_circle" "317.8625,-39.9693" "0.075")
(command "_circle" "317.8625,-39.6693" "0.075")
(command "_circle" "317.8625,-39.3693" "0.075")
(command "_circle" "317.8625,-39.0693" "0.075")
(command "_layer" "set" "nitride" "")
(setq coords (list 
(list 320.2625 -14.8263) 
(list 320.2625 100.8184) 
(list 319.7375 100.8184) 
(list 319.7375 -14.8263)))
(apply 'command (append '("pline") coords '("c")))
(setq currobj (ssadd (entlast) currobj))
(command "_layer" "set" "prebias" "")
(command "_rectangle" "319.7375,-14.8263" "320.2625,100.8184")
(setq currobj (ssadd (entlast) currobj))
(command "_layer" "set" "nitride" "")
(setq coords (list 
(list 320.2625 100.8184) 
(list 320.5625 110.8184) 
(list 320.5625 110.8184) 
(list 320.5625 111.8184) 
(list 394.585 111.0684) 
(list 394.585 116.0114) 
(list 320.5625 115.2614) 
(list 320.5625 116.2614) 
(list 320.5625 116.2614) 
(list 320.2625 126.2614) 
(list 319.7375 126.2614) 
(list 319.4375 116.2614) 
(list 319.4375 116.2614) 
(list 319.4375 115.2614) 
(list 245.415 116.0114) 
(list 245.415 111.0684) 
(list 319.4375 111.8184) 
(list 319.4375 110.8184) 
(list 319.4375 110.8184) 
(list 319.7375 100.8184)))
(apply 'command (append '("pline") coords '("c")))
(setq currobj (ssadd (entlast) currobj))
(command "_layer" "set" "prebias" "")
(setq coords (list 
(list 319.4375 100.8184) 
(list 319.4375 111.8184) 
(list 245.415 111.0684) 
(list 245.415 116.0114) 
(list 319.4375 115.2614) 
(list 319.4375 126.2614) 
(list 320.5625 126.2614) 
(list 320.5625 115.2614) 
(list 394.585 116.0114) 
(list 394.585 111.0684) 
(list 320.5625 111.8184) 
(list 320.5625 100.8184)))
(apply 'command (append '("pline") coords '("c")))
(setq currobj (ssadd (entlast) currobj))
(command "_layer" "set" "nitride" "")
(command "_layer" "set" "fda1" "")
(setq coords (list 
(list 320.5625 111.9614) 
(list 394.585 111.2114) 
(list 394.585 111.3884) 
(list 320.5625 112.0384)))
(apply 'command (append '("pline") coords '("c")))
(setq currobj (ssadd (entlast) currobj))
(setq coords (list 
(list 320.5625 112.1814) 
(list 394.585 111.5314) 
(list 394.585 111.7084) 
(list 320.5625 112.2584)))
(apply 'command (append '("pline") coords '("c")))
(setq currobj (ssadd (entlast) currobj))
(setq coords (list 
(list 320.5625 112.4014) 
(list 394.585 111.8514) 
(list 394.585 112.0284) 
(list 320.5625 112.4784)))
(apply 'command (append '("pline") coords '("c")))
(setq currobj (ssadd (entlast) currobj))
(setq coords (list 
(list 320.5625 112.6214) 
(list 394.585 112.1714) 
(list 394.585 112.3484) 
(list 320.5625 112.6984)))
(apply 'command (append '("pline") coords '("c")))
(setq currobj (ssadd (entlast) currobj))
(setq coords (list 
(list 320.5625 112.8414) 
(list 394.585 112.4914) 
(list 394.585 112.6684) 
(list 320.5625 112.9184)))
(apply 'command (append '("pline") coords '("c")))
(setq currobj (ssadd (entlast) currobj))
(setq coords (list 
(list 320.5625 113.0614) 
(list 394.585 112.8114) 
(list 394.585 112.9884) 
(list 320.5625 113.1384)))
(apply 'command (append '("pline") coords '("c")))
(setq currobj (ssadd (entlast) currobj))
(setq coords (list 
(list 320.5625 113.2814) 
(list 394.585 113.1314) 
(list 394.585 113.3084) 
(list 320.5625 113.3584)))
(apply 'command (append '("pline") coords '("c")))
(setq currobj (ssadd (entlast) currobj))
(setq coords (list 
(list 320.5625 113.5014) 
(list 394.585 113.4514) 
(list 394.585 113.6284) 
(list 320.5625 113.5784)))
(apply 'command (append '("pline") coords '("c")))
(setq currobj (ssadd (entlast) currobj))
(setq coords (list 
(list 320.5625 113.7214) 
(list 394.585 113.7714) 
(list 394.585 113.9484) 
(list 320.5625 113.7984)))
(apply 'command (append '("pline") coords '("c")))
(setq currobj (ssadd (entlast) currobj))
(setq coords (list 
(list 320.5625 113.9414) 
(list 394.585 114.0914) 
(list 394.585 114.2684) 
(list 320.5625 114.0184)))
(apply 'command (append '("pline") coords '("c")))
(setq currobj (ssadd (entlast) currobj))
(setq coords (list 
(list 320.5625 114.1614) 
(list 394.585 114.4114) 
(list 394.585 114.5884) 
(list 320.5625 114.2384)))
(apply 'command (append '("pline") coords '("c")))
(setq currobj (ssadd (entlast) currobj))
(setq coords (list 
(list 320.5625 114.3814) 
(list 394.585 114.7314) 
(list 394.585 114.9084) 
(list 320.5625 114.4584)))
(apply 'command (append '("pline") coords '("c")))
(setq currobj (ssadd (entlast) currobj))
(setq coords (list 
(list 320.5625 114.6014) 
(list 394.585 115.0514) 
(list 394.585 115.2284) 
(list 320.5625 114.6784)))
(apply 'command (append '("pline") coords '("c")))
(setq currobj (ssadd (entlast) currobj))
(setq coords (list 
(list 320.5625 114.8214) 
(list 394.585 115.3714) 
(list 394.585 115.5484) 
(list 320.5625 114.8984)))
(apply 'command (append '("pline") coords '("c")))
(setq currobj (ssadd (entlast) currobj))
(setq coords (list 
(list 320.5625 115.0414) 
(list 394.585 115.6914) 
(list 394.585 115.8684) 
(list 320.5625 115.1184)))
(apply 'command (append '("pline") coords '("c")))
(setq currobj (ssadd (entlast) currobj))
(setq coords (list 
(list 319.4375 115.1184) 
(list 245.415 115.8684) 
(list 245.415 115.6914) 
(list 319.4375 115.0414)))
(apply 'command (append '("pline") coords '("c")))
(setq currobj (ssadd (entlast) currobj))
(setq coords (list 
(list 319.4375 114.8984) 
(list 245.415 115.5484) 
(list 245.415 115.3714) 
(list 319.4375 114.8214)))
(apply 'command (append '("pline") coords '("c")))
(setq currobj (ssadd (entlast) currobj))
(setq coords (list 
(list 319.4375 114.6784) 
(list 245.415 115.2284) 
(list 245.415 115.0514) 
(list 319.4375 114.6014)))
(apply 'command (append '("pline") coords '("c")))
(setq currobj (ssadd (entlast) currobj))
(setq coords (list 
(list 319.4375 114.4584) 
(list 245.415 114.9084) 
(list 245.415 114.7314) 
(list 319.4375 114.3814)))
(apply 'command (append '("pline") coords '("c")))
(setq currobj (ssadd (entlast) currobj))
(setq coords (list 
(list 319.4375 114.2384) 
(list 245.415 114.5884) 
(list 245.415 114.4114) 
(list 319.4375 114.1614)))
(apply 'command (append '("pline") coords '("c")))
(setq currobj (ssadd (entlast) currobj))
(setq coords (list 
(list 319.4375 114.0184) 
(list 245.415 114.2684) 
(list 245.415 114.0914) 
(list 319.4375 113.9414)))
(apply 'command (append '("pline") coords '("c")))
(setq currobj (ssadd (entlast) currobj))
(setq coords (list 
(list 319.4375 113.7984) 
(list 245.415 113.9484) 
(list 245.415 113.7714) 
(list 319.4375 113.7214)))
(apply 'command (append '("pline") coords '("c")))
(setq currobj (ssadd (entlast) currobj))
(setq coords (list 
(list 319.4375 113.5784) 
(list 245.415 113.6284) 
(list 245.415 113.4514) 
(list 319.4375 113.5014)))
(apply 'command (append '("pline") coords '("c")))
(setq currobj (ssadd (entlast) currobj))
(setq coords (list 
(list 319.4375 113.3584) 
(list 245.415 113.3084) 
(list 245.415 113.1314) 
(list 319.4375 113.2814)))
(apply 'command (append '("pline") coords '("c")))
(setq currobj (ssadd (entlast) currobj))
(setq coords (list 
(list 319.4375 113.1384) 
(list 245.415 112.9884) 
(list 245.415 112.8114) 
(list 319.4375 113.0614)))
(apply 'command (append '("pline") coords '("c")))
(setq currobj (ssadd (entlast) currobj))
(setq coords (list 
(list 319.4375 112.9184) 
(list 245.415 112.6684) 
(list 245.415 112.4914) 
(list 319.4375 112.8414)))
(apply 'command (append '("pline") coords '("c")))
(setq currobj (ssadd (entlast) currobj))
(setq coords (list 
(list 319.4375 112.6984) 
(list 245.415 112.3484) 
(list 245.415 112.1714) 
(list 319.4375 112.6214)))
(apply 'command (append '("pline") coords '("c")))
(setq currobj (ssadd (entlast) currobj))
(setq coords (list 
(list 319.4375 112.4784) 
(list 245.415 112.0284) 
(list 245.415 111.8514) 
(list 319.4375 112.4014)))
(apply 'command (append '("pline") coords '("c")))
(setq currobj (ssadd (entlast) currobj))
(setq coords (list 
(list 319.4375 112.2584) 
(list 245.415 111.7084) 
(list 245.415 111.5314) 
(list 319.4375 112.1814)))
(apply 'command (append '("pline") coords '("c")))
(setq currobj (ssadd (entlast) currobj))
(setq coords (list 
(list 319.4375 112.0384) 
(list 245.415 111.3884) 
(list 245.415 111.2114) 
(list 319.4375 111.9614)))
(apply 'command (append '("pline") coords '("c")))
(setq currobj (ssadd (entlast) currobj))
(command "_layer" "set" "nitride" "")
(command "_layer" "set" "text" "")
(command "_circle" "319.0625,100.8184" "0.075")
(command "_circle" "319.0625,101.1184" "0.075")
(command "_circle" "319.0625,101.4184" "0.075")
(command "_circle" "319.0625,101.7184" "0.075")
(command "_circle" "319.0625,102.0184" "0.075")
(command "_circle" "318.7625,100.8184" "0.075")
(command "_circle" "318.7625,101.1184" "0.075")
(command "_circle" "318.7625,101.4184" "0.075")
(command "_circle" "318.7625,101.7184" "0.075")
(command "_circle" "318.7625,102.0184" "0.075")
(command "_circle" "318.4625,100.8184" "0.075")
(command "_circle" "318.4625,101.1184" "0.075")
(command "_circle" "318.4625,101.4184" "0.075")
(command "_circle" "318.4625,101.7184" "0.075")
(command "_circle" "318.4625,102.0184" "0.075")
(command "_circle" "318.1625,100.8184" "0.075")
(command "_circle" "318.1625,101.1184" "0.075")
(command "_circle" "318.1625,101.4184" "0.075")
(command "_circle" "318.1625,101.7184" "0.075")
(command "_circle" "318.1625,102.0184" "0.075")
(command "_circle" "317.8625,100.8184" "0.075")
(command "_circle" "317.8625,101.1184" "0.075")
(command "_circle" "317.8625,101.4184" "0.075")
(command "_circle" "317.8625,101.7184" "0.075")
(command "_circle" "317.8625,102.0184" "0.075")
(command "_layer" "set" "nitride" "")
(setq coords (list 
(list 320.2625 126.2614) 
(list 320.2625 241.9061) 
(list 319.7375 241.9061) 
(list 319.7375 126.2614)))
(apply 'command (append '("pline") coords '("c")))
(setq currobj (ssadd (entlast) currobj))
(command "_layer" "set" "prebias" "")
(command "_rectangle" "319.7375,126.2614" "320.2625,241.9061")
(setq currobj (ssadd (entlast) currobj))
(command "_layer" "set" "nitride" "")
(setq coords (list 
(list 320.2625 241.9061) 
(list 320.5625 251.9061) 
(list 320.5625 251.9061) 
(list 320.5625 252.9061) 
(list 394.585 252.1561) 
(list 394.585 257.0991) 
(list 320.5625 256.3491) 
(list 320.5625 257.3491) 
(list 320.5625 257.3491) 
(list 320.2625 267.3491) 
(list 319.7375 267.3491) 
(list 319.4375 257.3491) 
(list 319.4375 257.3491) 
(list 319.4375 256.3491) 
(list 245.415 257.0991) 
(list 245.415 252.1561) 
(list 319.4375 252.9061) 
(list 319.4375 251.9061) 
(list 319.4375 251.9061) 
(list 319.7375 241.9061)))
(apply 'command (append '("pline") coords '("c")))
(setq currobj (ssadd (entlast) currobj))
(command "_layer" "set" "prebias" "")
(setq coords (list 
(list 319.4375 241.9061) 
(list 319.4375 252.9061) 
(list 245.415 252.1561) 
(list 245.415 257.0991) 
(list 319.4375 256.3491) 
(list 319.4375 267.3491) 
(list 320.5625 267.3491) 
(list 320.5625 256.3491) 
(list 394.585 257.0991) 
(list 394.585 252.1561) 
(list 320.5625 252.9061) 
(list 320.5625 241.9061)))
(apply 'command (append '("pline") coords '("c")))
(setq currobj (ssadd (entlast) currobj))
(command "_layer" "set" "nitride" "")
(command "_layer" "set" "fda1" "")
(setq coords (list 
(list 320.5625 253.0491) 
(list 394.585 252.2991) 
(list 394.585 252.4761) 
(list 320.5625 253.1261)))
(apply 'command (append '("pline") coords '("c")))
(setq currobj (ssadd (entlast) currobj))
(setq coords (list 
(list 320.5625 253.2691) 
(list 394.585 252.6191) 
(list 394.585 252.7961) 
(list 320.5625 253.3461)))
(apply 'command (append '("pline") coords '("c")))
(setq currobj (ssadd (entlast) currobj))
(setq coords (list 
(list 320.5625 253.4891) 
(list 394.585 252.9391) 
(list 394.585 253.1161) 
(list 320.5625 253.5661)))
(apply 'command (append '("pline") coords '("c")))
(setq currobj (ssadd (entlast) currobj))
(setq coords (list 
(list 320.5625 253.7091) 
(list 394.585 253.2591) 
(list 394.585 253.4361) 
(list 320.5625 253.7861)))
(apply 'command (append '("pline") coords '("c")))
(setq currobj (ssadd (entlast) currobj))
(setq coords (list 
(list 320.5625 253.9291) 
(list 394.585 253.5791) 
(list 394.585 253.7561) 
(list 320.5625 254.0061)))
(apply 'command (append '("pline") coords '("c")))
(setq currobj (ssadd (entlast) currobj))
(setq coords (list 
(list 320.5625 254.1491) 
(list 394.585 253.8991) 
(list 394.585 254.0761) 
(list 320.5625 254.2261)))
(apply 'command (append '("pline") coords '("c")))
(setq currobj (ssadd (entlast) currobj))
(setq coords (list 
(list 320.5625 254.3691) 
(list 394.585 254.2191) 
(list 394.585 254.3961) 
(list 320.5625 254.4461)))
(apply 'command (append '("pline") coords '("c")))
(setq currobj (ssadd (entlast) currobj))
(setq coords (list 
(list 320.5625 254.5891) 
(list 394.585 254.5391) 
(list 394.585 254.7161) 
(list 320.5625 254.6661)))
(apply 'command (append '("pline") coords '("c")))
(setq currobj (ssadd (entlast) currobj))
(setq coords (list 
(list 320.5625 254.8091) 
(list 394.585 254.8591) 
(list 394.585 255.0361) 
(list 320.5625 254.8861)))
(apply 'command (append '("pline") coords '("c")))
(setq currobj (ssadd (entlast) currobj))
(setq coords (list 
(list 320.5625 255.0291) 
(list 394.585 255.1791) 
(list 394.585 255.3561) 
(list 320.5625 255.1061)))
(apply 'command (append '("pline") coords '("c")))
(setq currobj (ssadd (entlast) currobj))
(setq coords (list 
(list 320.5625 255.2491) 
(list 394.585 255.4991) 
(list 394.585 255.6761) 
(list 320.5625 255.3261)))
(apply 'command (append '("pline") coords '("c")))
(setq currobj (ssadd (entlast) currobj))
(setq coords (list 
(list 320.5625 255.4691) 
(list 394.585 255.8191) 
(list 394.585 255.9961) 
(list 320.5625 255.5461)))
(apply 'command (append '("pline") coords '("c")))
(setq currobj (ssadd (entlast) currobj))
(setq coords (list 
(list 320.5625 255.6891) 
(list 394.585 256.1391) 
(list 394.585 256.3161) 
(list 320.5625 255.7661)))
(apply 'command (append '("pline") coords '("c")))
(setq currobj (ssadd (entlast) currobj))
(setq coords (list 
(list 320.5625 255.9091) 
(list 394.585 256.4591) 
(list 394.585 256.6361) 
(list 320.5625 255.9861)))
(apply 'command (append '("pline") coords '("c")))
(setq currobj (ssadd (entlast) currobj))
(setq coords (list 
(list 320.5625 256.1291) 
(list 394.585 256.7791) 
(list 394.585 256.9561) 
(list 320.5625 256.2061)))
(apply 'command (append '("pline") coords '("c")))
(setq currobj (ssadd (entlast) currobj))
(setq coords (list 
(list 319.4375 256.2061) 
(list 245.415 256.9561) 
(list 245.415 256.7791) 
(list 319.4375 256.1291)))
(apply 'command (append '("pline") coords '("c")))
(setq currobj (ssadd (entlast) currobj))
(setq coords (list 
(list 319.4375 255.9861) 
(list 245.415 256.6361) 
(list 245.415 256.4591) 
(list 319.4375 255.9091)))
(apply 'command (append '("pline") coords '("c")))
(setq currobj (ssadd (entlast) currobj))
(setq coords (list 
(list 319.4375 255.7661) 
(list 245.415 256.3161) 
(list 245.415 256.1391) 
(list 319.4375 255.6891)))
(apply 'command (append '("pline") coords '("c")))
(setq currobj (ssadd (entlast) currobj))
(setq coords (list 
(list 319.4375 255.5461) 
(list 245.415 255.9961) 
(list 245.415 255.8191) 
(list 319.4375 255.4691)))
(apply 'command (append '("pline") coords '("c")))
(setq currobj (ssadd (entlast) currobj))
(setq coords (list 
(list 319.4375 255.3261) 
(list 245.415 255.6761) 
(list 245.415 255.4991) 
(list 319.4375 255.2491)))
(apply 'command (append '("pline") coords '("c")))
(setq currobj (ssadd (entlast) currobj))
(setq coords (list 
(list 319.4375 255.1061) 
(list 245.415 255.3561) 
(list 245.415 255.1791) 
(list 319.4375 255.0291)))
(apply 'command (append '("pline") coords '("c")))
(setq currobj (ssadd (entlast) currobj))
(setq coords (list 
(list 319.4375 254.8861) 
(list 245.415 255.0361) 
(list 245.415 254.8591) 
(list 319.4375 254.8091)))
(apply 'command (append '("pline") coords '("c")))
(setq currobj (ssadd (entlast) currobj))
(setq coords (list 
(list 319.4375 254.6661) 
(list 245.415 254.7161) 
(list 245.415 254.5391) 
(list 319.4375 254.5891)))
(apply 'command (append '("pline") coords '("c")))
(setq currobj (ssadd (entlast) currobj))
(setq coords (list 
(list 319.4375 254.4461) 
(list 245.415 254.3961) 
(list 245.415 254.2191) 
(list 319.4375 254.3691)))
(apply 'command (append '("pline") coords '("c")))
(setq currobj (ssadd (entlast) currobj))
(setq coords (list 
(list 319.4375 254.2261) 
(list 245.415 254.0761) 
(list 245.415 253.8991) 
(list 319.4375 254.1491)))
(apply 'command (append '("pline") coords '("c")))
(setq currobj (ssadd (entlast) currobj))
(setq coords (list 
(list 319.4375 254.0061) 
(list 245.415 253.7561) 
(list 245.415 253.5791) 
(list 319.4375 253.9291)))
(apply 'command (append '("pline") coords '("c")))
(setq currobj (ssadd (entlast) currobj))
(setq coords (list 
(list 319.4375 253.7861) 
(list 245.415 253.4361) 
(list 245.415 253.2591) 
(list 319.4375 253.7091)))
(apply 'command (append '("pline") coords '("c")))
(setq currobj (ssadd (entlast) currobj))
(setq coords (list 
(list 319.4375 253.5661) 
(list 245.415 253.1161) 
(list 245.415 252.9391) 
(list 319.4375 253.4891)))
(apply 'command (append '("pline") coords '("c")))
(setq currobj (ssadd (entlast) currobj))
(setq coords (list 
(list 319.4375 253.3461) 
(list 245.415 252.7961) 
(list 245.415 252.6191) 
(list 319.4375 253.2691)))
(apply 'command (append '("pline") coords '("c")))
(setq currobj (ssadd (entlast) currobj))
(setq coords (list 
(list 319.4375 253.1261) 
(list 245.415 252.4761) 
(list 245.415 252.2991) 
(list 319.4375 253.0491)))
(apply 'command (append '("pline") coords '("c")))
(setq currobj (ssadd (entlast) currobj))
(command "_layer" "set" "nitride" "")
(command "_layer" "set" "text" "")
(command "_circle" "319.0625,241.9061" "0.075")
(command "_circle" "319.0625,242.2061" "0.075")
(command "_circle" "319.0625,242.5061" "0.075")
(command "_circle" "319.0625,242.8061" "0.075")
(command "_circle" "319.0625,243.1061" "0.075")
(command "_circle" "318.7625,241.9061" "0.075")
(command "_circle" "318.7625,242.2061" "0.075")
(command "_circle" "318.7625,242.5061" "0.075")
(command "_circle" "318.7625,242.8061" "0.075")
(command "_circle" "318.7625,243.1061" "0.075")
(command "_circle" "318.4625,241.9061" "0.075")
(command "_circle" "318.4625,242.2061" "0.075")
(command "_circle" "318.4625,242.5061" "0.075")
(command "_circle" "318.4625,242.8061" "0.075")
(command "_circle" "318.4625,243.1061" "0.075")
(command "_circle" "318.1625,241.9061" "0.075")
(command "_circle" "318.1625,242.2061" "0.075")
(command "_circle" "318.1625,242.5061" "0.075")
(command "_circle" "318.1625,242.8061" "0.075")
(command "_circle" "318.1625,243.1061" "0.075")
(command "_circle" "317.8625,241.9061" "0.075")
(command "_circle" "317.8625,242.2061" "0.075")
(command "_circle" "317.8625,242.5061" "0.075")
(command "_circle" "317.8625,242.8061" "0.075")
(command "_circle" "317.8625,243.1061" "0.075")
(command "_layer" "set" "nitride" "")
(setq coords (list 
(list 320.2625 267.3491) 
(list 320.2625 382.9939) 
(list 319.7375 382.9939) 
(list 319.7375 267.3491)))
(apply 'command (append '("pline") coords '("c")))
(setq currobj (ssadd (entlast) currobj))
(command "_layer" "set" "prebias" "")
(command "_rectangle" "319.7375,267.3491" "320.2625,382.9939")
(setq currobj (ssadd (entlast) currobj))
(command "_layer" "set" "nitride" "")
(setq coords (list 
(list 320.2625 382.9939) 
(list 320.5625 392.9939) 
(list 320.5625 392.9939) 
(list 320.5625 393.9939) 
(list 394.585 393.2439) 
(list 394.585 398.1869) 
(list 320.5625 397.4369) 
(list 320.5625 398.4369) 
(list 320.5625 398.4369) 
(list 320.2625 408.4369) 
(list 319.7375 408.4369) 
(list 319.4375 398.4369) 
(list 319.4375 398.4369) 
(list 319.4375 397.4369) 
(list 245.415 398.1869) 
(list 245.415 393.2439) 
(list 319.4375 393.9939) 
(list 319.4375 392.9939) 
(list 319.4375 392.9939) 
(list 319.7375 382.9939)))
(apply 'command (append '("pline") coords '("c")))
(setq currobj (ssadd (entlast) currobj))
(command "_layer" "set" "prebias" "")
(setq coords (list 
(list 319.4375 382.9939) 
(list 319.4375 393.9939) 
(list 245.415 393.2439) 
(list 245.415 398.1869) 
(list 319.4375 397.4369) 
(list 319.4375 408.4369) 
(list 320.5625 408.4369) 
(list 320.5625 397.4369) 
(list 394.585 398.1869) 
(list 394.585 393.2439) 
(list 320.5625 393.9939) 
(list 320.5625 382.9939)))
(apply 'command (append '("pline") coords '("c")))
(setq currobj (ssadd (entlast) currobj))
(command "_layer" "set" "nitride" "")
(command "_layer" "set" "fda1" "")
(setq coords (list 
(list 320.5625 394.1369) 
(list 394.585 393.3869) 
(list 394.585 393.5639) 
(list 320.5625 394.2139)))
(apply 'command (append '("pline") coords '("c")))
(setq currobj (ssadd (entlast) currobj))
(setq coords (list 
(list 320.5625 394.3569) 
(list 394.585 393.7069) 
(list 394.585 393.8839) 
(list 320.5625 394.4339)))
(apply 'command (append '("pline") coords '("c")))
(setq currobj (ssadd (entlast) currobj))
(setq coords (list 
(list 320.5625 394.5769) 
(list 394.585 394.0269) 
(list 394.585 394.2039) 
(list 320.5625 394.6539)))
(apply 'command (append '("pline") coords '("c")))
(setq currobj (ssadd (entlast) currobj))
(setq coords (list 
(list 320.5625 394.7969) 
(list 394.585 394.3469) 
(list 394.585 394.5239) 
(list 320.5625 394.8739)))
(apply 'command (append '("pline") coords '("c")))
(setq currobj (ssadd (entlast) currobj))
(setq coords (list 
(list 320.5625 395.0169) 
(list 394.585 394.6669) 
(list 394.585 394.8439) 
(list 320.5625 395.0939)))
(apply 'command (append '("pline") coords '("c")))
(setq currobj (ssadd (entlast) currobj))
(setq coords (list 
(list 320.5625 395.2369) 
(list 394.585 394.9869) 
(list 394.585 395.1639) 
(list 320.5625 395.3139)))
(apply 'command (append '("pline") coords '("c")))
(setq currobj (ssadd (entlast) currobj))
(setq coords (list 
(list 320.5625 395.4569) 
(list 394.585 395.3069) 
(list 394.585 395.4839) 
(list 320.5625 395.5339)))
(apply 'command (append '("pline") coords '("c")))
(setq currobj (ssadd (entlast) currobj))
(setq coords (list 
(list 320.5625 395.6769) 
(list 394.585 395.6269) 
(list 394.585 395.8039) 
(list 320.5625 395.7539)))
(apply 'command (append '("pline") coords '("c")))
(setq currobj (ssadd (entlast) currobj))
(setq coords (list 
(list 320.5625 395.8969) 
(list 394.585 395.9469) 
(list 394.585 396.1239) 
(list 320.5625 395.9739)))
(apply 'command (append '("pline") coords '("c")))
(setq currobj (ssadd (entlast) currobj))
(setq coords (list 
(list 320.5625 396.1169) 
(list 394.585 396.2669) 
(list 394.585 396.4439) 
(list 320.5625 396.1939)))
(apply 'command (append '("pline") coords '("c")))
(setq currobj (ssadd (entlast) currobj))
(setq coords (list 
(list 320.5625 396.3369) 
(list 394.585 396.5869) 
(list 394.585 396.7639) 
(list 320.5625 396.4139)))
(apply 'command (append '("pline") coords '("c")))
(setq currobj (ssadd (entlast) currobj))
(setq coords (list 
(list 320.5625 396.5569) 
(list 394.585 396.9069) 
(list 394.585 397.0839) 
(list 320.5625 396.6339)))
(apply 'command (append '("pline") coords '("c")))
(setq currobj (ssadd (entlast) currobj))
(setq coords (list 
(list 320.5625 396.7769) 
(list 394.585 397.2269) 
(list 394.585 397.4039) 
(list 320.5625 396.8539)))
(apply 'command (append '("pline") coords '("c")))
(setq currobj (ssadd (entlast) currobj))
(setq coords (list 
(list 320.5625 396.9969) 
(list 394.585 397.5469) 
(list 394.585 397.7239) 
(list 320.5625 397.0739)))
(apply 'command (append '("pline") coords '("c")))
(setq currobj (ssadd (entlast) currobj))
(setq coords (list 
(list 320.5625 397.2169) 
(list 394.585 397.8669) 
(list 394.585 398.0439) 
(list 320.5625 397.2939)))
(apply 'command (append '("pline") coords '("c")))
(setq currobj (ssadd (entlast) currobj))
(setq coords (list 
(list 319.4375 397.2939) 
(list 245.415 398.0439) 
(list 245.415 397.8669) 
(list 319.4375 397.2169)))
(apply 'command (append '("pline") coords '("c")))
(setq currobj (ssadd (entlast) currobj))
(setq coords (list 
(list 319.4375 397.0739) 
(list 245.415 397.7239) 
(list 245.415 397.5469) 
(list 319.4375 396.9969)))
(apply 'command (append '("pline") coords '("c")))
(setq currobj (ssadd (entlast) currobj))
(setq coords (list 
(list 319.4375 396.8539) 
(list 245.415 397.4039) 
(list 245.415 397.2269) 
(list 319.4375 396.7769)))
(apply 'command (append '("pline") coords '("c")))
(setq currobj (ssadd (entlast) currobj))
(setq coords (list 
(list 319.4375 396.6339) 
(list 245.415 397.0839) 
(list 245.415 396.9069) 
(list 319.4375 396.5569)))
(apply 'command (append '("pline") coords '("c")))
(setq currobj (ssadd (entlast) currobj))
(setq coords (list 
(list 319.4375 396.4139) 
(list 245.415 396.7639) 
(list 245.415 396.5869) 
(list 319.4375 396.3369)))
(apply 'command (append '("pline") coords '("c")))
(setq currobj (ssadd (entlast) currobj))
(setq coords (list 
(list 319.4375 396.1939) 
(list 245.415 396.4439) 
(list 245.415 396.2669) 
(list 319.4375 396.1169)))
(apply 'command (append '("pline") coords '("c")))
(setq currobj (ssadd (entlast) currobj))
(setq coords (list 
(list 319.4375 395.9739) 
(list 245.415 396.1239) 
(list 245.415 395.9469) 
(list 319.4375 395.8969)))
(apply 'command (append '("pline") coords '("c")))
(setq currobj (ssadd (entlast) currobj))
(setq coords (list 
(list 319.4375 395.7539) 
(list 245.415 395.8039) 
(list 245.415 395.6269) 
(list 319.4375 395.6769)))
(apply 'command (append '("pline") coords '("c")))
(setq currobj (ssadd (entlast) currobj))
(setq coords (list 
(list 319.4375 395.5339) 
(list 245.415 395.4839) 
(list 245.415 395.3069) 
(list 319.4375 395.4569)))
(apply 'command (append '("pline") coords '("c")))
(setq currobj (ssadd (entlast) currobj))
(setq coords (list 
(list 319.4375 395.3139) 
(list 245.415 395.1639) 
(list 245.415 394.9869) 
(list 319.4375 395.2369)))
(apply 'command (append '("pline") coords '("c")))
(setq currobj (ssadd (entlast) currobj))
(setq coords (list 
(list 319.4375 395.0939) 
(list 245.415 394.8439) 
(list 245.415 394.6669) 
(list 319.4375 395.0169)))
(apply 'command (append '("pline") coords '("c")))
(setq currobj (ssadd (entlast) currobj))
(setq coords (list 
(list 319.4375 394.8739) 
(list 245.415 394.5239) 
(list 245.415 394.3469) 
(list 319.4375 394.7969)))
(apply 'command (append '("pline") coords '("c")))
(setq currobj (ssadd (entlast) currobj))
(setq coords (list 
(list 319.4375 394.6539) 
(list 245.415 394.2039) 
(list 245.415 394.0269) 
(list 319.4375 394.5769)))
(apply 'command (append '("pline") coords '("c")))
(setq currobj (ssadd (entlast) currobj))
(setq coords (list 
(list 319.4375 394.4339) 
(list 245.415 393.8839) 
(list 245.415 393.7069) 
(list 319.4375 394.3569)))
(apply 'command (append '("pline") coords '("c")))
(setq currobj (ssadd (entlast) currobj))
(setq coords (list 
(list 319.4375 394.2139) 
(list 245.415 393.5639) 
(list 245.415 393.3869) 
(list 319.4375 394.1369)))
(apply 'command (append '("pline") coords '("c")))
(setq currobj (ssadd (entlast) currobj))
(command "_layer" "set" "nitride" "")
(command "_layer" "set" "text" "")
(command "_circle" "319.0625,382.9939" "0.075")
(command "_circle" "319.0625,383.2939" "0.075")
(command "_circle" "319.0625,383.5939" "0.075")
(command "_circle" "319.0625,383.8939" "0.075")
(command "_circle" "319.0625,384.1939" "0.075")
(command "_circle" "318.7625,382.9939" "0.075")
(command "_circle" "318.7625,383.2939" "0.075")
(command "_circle" "318.7625,383.5939" "0.075")
(command "_circle" "318.7625,383.8939" "0.075")
(command "_circle" "318.7625,384.1939" "0.075")
(command "_circle" "318.4625,382.9939" "0.075")
(command "_circle" "318.4625,383.2939" "0.075")
(command "_circle" "318.4625,383.5939" "0.075")
(command "_circle" "318.4625,383.8939" "0.075")
(command "_circle" "318.4625,384.1939" "0.075")
(command "_circle" "318.1625,382.9939" "0.075")
(command "_circle" "318.1625,383.2939" "0.075")
(command "_circle" "318.1625,383.5939" "0.075")
(command "_circle" "318.1625,383.8939" "0.075")
(command "_circle" "318.1625,384.1939" "0.075")
(command "_circle" "317.8625,382.9939" "0.075")
(command "_circle" "317.8625,383.2939" "0.075")
(command "_circle" "317.8625,383.5939" "0.075")
(command "_circle" "317.8625,383.8939" "0.075")
(command "_circle" "317.8625,384.1939" "0.075")
(command "_layer" "set" "nitride" "")
(setq coords (list 
(list 320.2625 408.4369) 
(list 320.2625 524.0816) 
(list 319.7375 524.0816) 
(list 319.7375 408.4369)))
(apply 'command (append '("pline") coords '("c")))
(setq currobj (ssadd (entlast) currobj))
(command "_layer" "set" "prebias" "")
(command "_rectangle" "319.7375,408.4369" "320.2625,524.0816")
(setq currobj (ssadd (entlast) currobj))
(command "_layer" "set" "nitride" "")
(setq coords (list 
(list 320.2625 524.0816) 
(list 320.5625 534.0816) 
(list 320.5625 534.0816) 
(list 320.5625 535.0816) 
(list 394.585 534.3316) 
(list 394.585 539.2746) 
(list 320.5625 538.5246) 
(list 320.5625 539.5246) 
(list 320.5625 539.5246) 
(list 320.2625 549.5246) 
(list 319.7375 549.5246) 
(list 319.4375 539.5246) 
(list 319.4375 539.5246) 
(list 319.4375 538.5246) 
(list 245.415 539.2746) 
(list 245.415 534.3316) 
(list 319.4375 535.0816) 
(list 319.4375 534.0816) 
(list 319.4375 534.0816) 
(list 319.7375 524.0816)))
(apply 'command (append '("pline") coords '("c")))
(setq currobj (ssadd (entlast) currobj))
(command "_layer" "set" "prebias" "")
(setq coords (list 
(list 319.4375 524.0816) 
(list 319.4375 535.0816) 
(list 245.415 534.3316) 
(list 245.415 539.2746) 
(list 319.4375 538.5246) 
(list 319.4375 549.5246) 
(list 320.5625 549.5246) 
(list 320.5625 538.5246) 
(list 394.585 539.2746) 
(list 394.585 534.3316) 
(list 320.5625 535.0816) 
(list 320.5625 524.0816)))
(apply 'command (append '("pline") coords '("c")))
(setq currobj (ssadd (entlast) currobj))
(command "_layer" "set" "nitride" "")
(command "_layer" "set" "fda1" "")
(setq coords (list 
(list 320.5625 535.2246) 
(list 394.585 534.4746) 
(list 394.585 534.6516) 
(list 320.5625 535.3016)))
(apply 'command (append '("pline") coords '("c")))
(setq currobj (ssadd (entlast) currobj))
(setq coords (list 
(list 320.5625 535.4446) 
(list 394.585 534.7946) 
(list 394.585 534.9716) 
(list 320.5625 535.5216)))
(apply 'command (append '("pline") coords '("c")))
(setq currobj (ssadd (entlast) currobj))
(setq coords (list 
(list 320.5625 535.6646) 
(list 394.585 535.1146) 
(list 394.585 535.2916) 
(list 320.5625 535.7416)))
(apply 'command (append '("pline") coords '("c")))
(setq currobj (ssadd (entlast) currobj))
(setq coords (list 
(list 320.5625 535.8846) 
(list 394.585 535.4346) 
(list 394.585 535.6116) 
(list 320.5625 535.9616)))
(apply 'command (append '("pline") coords '("c")))
(setq currobj (ssadd (entlast) currobj))
(setq coords (list 
(list 320.5625 536.1046) 
(list 394.585 535.7546) 
(list 394.585 535.9316) 
(list 320.5625 536.1816)))
(apply 'command (append '("pline") coords '("c")))
(setq currobj (ssadd (entlast) currobj))
(setq coords (list 
(list 320.5625 536.3246) 
(list 394.585 536.0746) 
(list 394.585 536.2516) 
(list 320.5625 536.4016)))
(apply 'command (append '("pline") coords '("c")))
(setq currobj (ssadd (entlast) currobj))
(setq coords (list 
(list 320.5625 536.5446) 
(list 394.585 536.3946) 
(list 394.585 536.5716) 
(list 320.5625 536.6216)))
(apply 'command (append '("pline") coords '("c")))
(setq currobj (ssadd (entlast) currobj))
(setq coords (list 
(list 320.5625 536.7646) 
(list 394.585 536.7146) 
(list 394.585 536.8916) 
(list 320.5625 536.8416)))
(apply 'command (append '("pline") coords '("c")))
(setq currobj (ssadd (entlast) currobj))
(setq coords (list 
(list 320.5625 536.9846) 
(list 394.585 537.0346) 
(list 394.585 537.2116) 
(list 320.5625 537.0616)))
(apply 'command (append '("pline") coords '("c")))
(setq currobj (ssadd (entlast) currobj))
(setq coords (list 
(list 320.5625 537.2046) 
(list 394.585 537.3546) 
(list 394.585 537.5316) 
(list 320.5625 537.2816)))
(apply 'command (append '("pline") coords '("c")))
(setq currobj (ssadd (entlast) currobj))
(setq coords (list 
(list 320.5625 537.4246) 
(list 394.585 537.6746) 
(list 394.585 537.8516) 
(list 320.5625 537.5016)))
(apply 'command (append '("pline") coords '("c")))
(setq currobj (ssadd (entlast) currobj))
(setq coords (list 
(list 320.5625 537.6446) 
(list 394.585 537.9946) 
(list 394.585 538.1716) 
(list 320.5625 537.7216)))
(apply 'command (append '("pline") coords '("c")))
(setq currobj (ssadd (entlast) currobj))
(setq coords (list 
(list 320.5625 537.8646) 
(list 394.585 538.3146) 
(list 394.585 538.4916) 
(list 320.5625 537.9416)))
(apply 'command (append '("pline") coords '("c")))
(setq currobj (ssadd (entlast) currobj))
(setq coords (list 
(list 320.5625 538.0846) 
(list 394.585 538.6346) 
(list 394.585 538.8116) 
(list 320.5625 538.1616)))
(apply 'command (append '("pline") coords '("c")))
(setq currobj (ssadd (entlast) currobj))
(setq coords (list 
(list 320.5625 538.3046) 
(list 394.585 538.9546) 
(list 394.585 539.1316) 
(list 320.5625 538.3816)))
(apply 'command (append '("pline") coords '("c")))
(setq currobj (ssadd (entlast) currobj))
(setq coords (list 
(list 319.4375 538.3816) 
(list 245.415 539.1316) 
(list 245.415 538.9546) 
(list 319.4375 538.3046)))
(apply 'command (append '("pline") coords '("c")))
(setq currobj (ssadd (entlast) currobj))
(setq coords (list 
(list 319.4375 538.1616) 
(list 245.415 538.8116) 
(list 245.415 538.6346) 
(list 319.4375 538.0846)))
(apply 'command (append '("pline") coords '("c")))
(setq currobj (ssadd (entlast) currobj))
(setq coords (list 
(list 319.4375 537.9416) 
(list 245.415 538.4916) 
(list 245.415 538.3146) 
(list 319.4375 537.8646)))
(apply 'command (append '("pline") coords '("c")))
(setq currobj (ssadd (entlast) currobj))
(setq coords (list 
(list 319.4375 537.7216) 
(list 245.415 538.1716) 
(list 245.415 537.9946) 
(list 319.4375 537.6446)))
(apply 'command (append '("pline") coords '("c")))
(setq currobj (ssadd (entlast) currobj))
(setq coords (list 
(list 319.4375 537.5016) 
(list 245.415 537.8516) 
(list 245.415 537.6746) 
(list 319.4375 537.4246)))
(apply 'command (append '("pline") coords '("c")))
(setq currobj (ssadd (entlast) currobj))
(setq coords (list 
(list 319.4375 537.2816) 
(list 245.415 537.5316) 
(list 245.415 537.3546) 
(list 319.4375 537.2046)))
(apply 'command (append '("pline") coords '("c")))
(setq currobj (ssadd (entlast) currobj))
(setq coords (list 
(list 319.4375 537.0616) 
(list 245.415 537.2116) 
(list 245.415 537.0346) 
(list 319.4375 536.9846)))
(apply 'command (append '("pline") coords '("c")))
(setq currobj (ssadd (entlast) currobj))
(setq coords (list 
(list 319.4375 536.8416) 
(list 245.415 536.8916) 
(list 245.415 536.7146) 
(list 319.4375 536.7646)))
(apply 'command (append '("pline") coords '("c")))
(setq currobj (ssadd (entlast) currobj))
(setq coords (list 
(list 319.4375 536.6216) 
(list 245.415 536.5716) 
(list 245.415 536.3946) 
(list 319.4375 536.5446)))
(apply 'command (append '("pline") coords '("c")))
(setq currobj (ssadd (entlast) currobj))
(setq coords (list 
(list 319.4375 536.4016) 
(list 245.415 536.2516) 
(list 245.415 536.0746) 
(list 319.4375 536.3246)))
(apply 'command (append '("pline") coords '("c")))
(setq currobj (ssadd (entlast) currobj))
(setq coords (list 
(list 319.4375 536.1816) 
(list 245.415 535.9316) 
(list 245.415 535.7546) 
(list 319.4375 536.1046)))
(apply 'command (append '("pline") coords '("c")))
(setq currobj (ssadd (entlast) currobj))
(setq coords (list 
(list 319.4375 535.9616) 
(list 245.415 535.6116) 
(list 245.415 535.4346) 
(list 319.4375 535.8846)))
(apply 'command (append '("pline") coords '("c")))
(setq currobj (ssadd (entlast) currobj))
(setq coords (list 
(list 319.4375 535.7416) 
(list 245.415 535.2916) 
(list 245.415 535.1146) 
(list 319.4375 535.6646)))
(apply 'command (append '("pline") coords '("c")))
(setq currobj (ssadd (entlast) currobj))
(setq coords (list 
(list 319.4375 535.5216) 
(list 245.415 534.9716) 
(list 245.415 534.7946) 
(list 319.4375 535.4446)))
(apply 'command (append '("pline") coords '("c")))
(setq currobj (ssadd (entlast) currobj))
(setq coords (list 
(list 319.4375 535.3016) 
(list 245.415 534.6516) 
(list 245.415 534.4746) 
(list 319.4375 535.2246)))
(apply 'command (append '("pline") coords '("c")))
(setq currobj (ssadd (entlast) currobj))
(command "_layer" "set" "nitride" "")
(command "_layer" "set" "text" "")
(command "_circle" "319.0625,524.0816" "0.075")
(command "_circle" "319.0625,524.3816" "0.075")
(command "_circle" "319.0625,524.6816" "0.075")
(command "_circle" "319.0625,524.9816" "0.075")
(command "_circle" "319.0625,525.2816" "0.075")
(command "_circle" "318.7625,524.0816" "0.075")
(command "_circle" "318.7625,524.3816" "0.075")
(command "_circle" "318.7625,524.6816" "0.075")
(command "_circle" "318.7625,524.9816" "0.075")
(command "_circle" "318.7625,525.2816" "0.075")
(command "_circle" "318.4625,524.0816" "0.075")
(command "_circle" "318.4625,524.3816" "0.075")
(command "_circle" "318.4625,524.6816" "0.075")
(command "_circle" "318.4625,524.9816" "0.075")
(command "_circle" "318.4625,525.2816" "0.075")
(command "_circle" "318.1625,524.0816" "0.075")
(command "_circle" "318.1625,524.3816" "0.075")
(command "_circle" "318.1625,524.6816" "0.075")
(command "_circle" "318.1625,524.9816" "0.075")
(command "_circle" "318.1625,525.2816" "0.075")
(command "_circle" "317.8625,524.0816" "0.075")
(command "_circle" "317.8625,524.3816" "0.075")
(command "_circle" "317.8625,524.6816" "0.075")
(command "_circle" "317.8625,524.9816" "0.075")
(command "_circle" "317.8625,525.2816" "0.075")
(command "_layer" "set" "nitride" "")
(setq coords (list 
(list 320.2625 549.5246) 
(list 320.2625 665.1693) 
(list 319.7375 665.1693) 
(list 319.7375 549.5246)))
(apply 'command (append '("pline") coords '("c")))
(setq currobj (ssadd (entlast) currobj))
(command "_layer" "set" "prebias" "")
(command "_rectangle" "319.7375,549.5246" "320.2625,665.1693")
(setq currobj (ssadd (entlast) currobj))
(command "_layer" "set" "nitride" "")
(setq coords (list 
(list 320.2625 665.1693) 
(list 320.5625 675.1693) 
(list 320.5625 675.1693) 
(list 320.5625 676.1693) 
(list 394.585 675.4193) 
(list 394.585 680.3623) 
(list 320.5625 679.6123) 
(list 320.5625 680.6123) 
(list 320.5625 680.6123) 
(list 320.2625 690.6123) 
(list 319.7375 690.6123) 
(list 319.4375 680.6123) 
(list 319.4375 680.6123) 
(list 319.4375 679.6123) 
(list 245.415 680.3623) 
(list 245.415 675.4193) 
(list 319.4375 676.1693) 
(list 319.4375 675.1693) 
(list 319.4375 675.1693) 
(list 319.7375 665.1693)))
(apply 'command (append '("pline") coords '("c")))
(setq currobj (ssadd (entlast) currobj))
(command "_layer" "set" "prebias" "")
(setq coords (list 
(list 319.4375 665.1693) 
(list 319.4375 676.1693) 
(list 245.415 675.4193) 
(list 245.415 680.3623) 
(list 319.4375 679.6123) 
(list 319.4375 690.6123) 
(list 320.5625 690.6123) 
(list 320.5625 679.6123) 
(list 394.585 680.3623) 
(list 394.585 675.4193) 
(list 320.5625 676.1693) 
(list 320.5625 665.1693)))
(apply 'command (append '("pline") coords '("c")))
(setq currobj (ssadd (entlast) currobj))
(command "_layer" "set" "nitride" "")
(command "_layer" "set" "fda1" "")
(setq coords (list 
(list 320.5625 676.3123) 
(list 394.585 675.5623) 
(list 394.585 675.7393) 
(list 320.5625 676.3893)))
(apply 'command (append '("pline") coords '("c")))
(setq currobj (ssadd (entlast) currobj))
(setq coords (list 
(list 320.5625 676.5323) 
(list 394.585 675.8823) 
(list 394.585 676.0593) 
(list 320.5625 676.6093)))
(apply 'command (append '("pline") coords '("c")))
(setq currobj (ssadd (entlast) currobj))
(setq coords (list 
(list 320.5625 676.7523) 
(list 394.585 676.2023) 
(list 394.585 676.3793) 
(list 320.5625 676.8293)))
(apply 'command (append '("pline") coords '("c")))
(setq currobj (ssadd (entlast) currobj))
(setq coords (list 
(list 320.5625 676.9723) 
(list 394.585 676.5223) 
(list 394.585 676.6993) 
(list 320.5625 677.0493)))
(apply 'command (append '("pline") coords '("c")))
(setq currobj (ssadd (entlast) currobj))
(setq coords (list 
(list 320.5625 677.1923) 
(list 394.585 676.8423) 
(list 394.585 677.0193) 
(list 320.5625 677.2693)))
(apply 'command (append '("pline") coords '("c")))
(setq currobj (ssadd (entlast) currobj))
(setq coords (list 
(list 320.5625 677.4123) 
(list 394.585 677.1623) 
(list 394.585 677.3393) 
(list 320.5625 677.4893)))
(apply 'command (append '("pline") coords '("c")))
(setq currobj (ssadd (entlast) currobj))
(setq coords (list 
(list 320.5625 677.6323) 
(list 394.585 677.4823) 
(list 394.585 677.6593) 
(list 320.5625 677.7093)))
(apply 'command (append '("pline") coords '("c")))
(setq currobj (ssadd (entlast) currobj))
(setq coords (list 
(list 320.5625 677.8523) 
(list 394.585 677.8023) 
(list 394.585 677.9793) 
(list 320.5625 677.9293)))
(apply 'command (append '("pline") coords '("c")))
(setq currobj (ssadd (entlast) currobj))
(setq coords (list 
(list 320.5625 678.0723) 
(list 394.585 678.1223) 
(list 394.585 678.2993) 
(list 320.5625 678.1493)))
(apply 'command (append '("pline") coords '("c")))
(setq currobj (ssadd (entlast) currobj))
(setq coords (list 
(list 320.5625 678.2923) 
(list 394.585 678.4423) 
(list 394.585 678.6193) 
(list 320.5625 678.3693)))
(apply 'command (append '("pline") coords '("c")))
(setq currobj (ssadd (entlast) currobj))
(setq coords (list 
(list 320.5625 678.5123) 
(list 394.585 678.7623) 
(list 394.585 678.9393) 
(list 320.5625 678.5893)))
(apply 'command (append '("pline") coords '("c")))
(setq currobj (ssadd (entlast) currobj))
(setq coords (list 
(list 320.5625 678.7323) 
(list 394.585 679.0823) 
(list 394.585 679.2593) 
(list 320.5625 678.8093)))
(apply 'command (append '("pline") coords '("c")))
(setq currobj (ssadd (entlast) currobj))
(setq coords (list 
(list 320.5625 678.9523) 
(list 394.585 679.4023) 
(list 394.585 679.5793) 
(list 320.5625 679.0293)))
(apply 'command (append '("pline") coords '("c")))
(setq currobj (ssadd (entlast) currobj))
(setq coords (list 
(list 320.5625 679.1723) 
(list 394.585 679.7223) 
(list 394.585 679.8993) 
(list 320.5625 679.2493)))
(apply 'command (append '("pline") coords '("c")))
(setq currobj (ssadd (entlast) currobj))
(setq coords (list 
(list 320.5625 679.3923) 
(list 394.585 680.0423) 
(list 394.585 680.2193) 
(list 320.5625 679.4693)))
(apply 'command (append '("pline") coords '("c")))
(setq currobj (ssadd (entlast) currobj))
(setq coords (list 
(list 319.4375 679.4693) 
(list 245.415 680.2193) 
(list 245.415 680.0423) 
(list 319.4375 679.3923)))
(apply 'command (append '("pline") coords '("c")))
(setq currobj (ssadd (entlast) currobj))
(setq coords (list 
(list 319.4375 679.2493) 
(list 245.415 679.8993) 
(list 245.415 679.7223) 
(list 319.4375 679.1723)))
(apply 'command (append '("pline") coords '("c")))
(setq currobj (ssadd (entlast) currobj))
(setq coords (list 
(list 319.4375 679.0293) 
(list 245.415 679.5793) 
(list 245.415 679.4023) 
(list 319.4375 678.9523)))
(apply 'command (append '("pline") coords '("c")))
(setq currobj (ssadd (entlast) currobj))
(setq coords (list 
(list 319.4375 678.8093) 
(list 245.415 679.2593) 
(list 245.415 679.0823) 
(list 319.4375 678.7323)))
(apply 'command (append '("pline") coords '("c")))
(setq currobj (ssadd (entlast) currobj))
(setq coords (list 
(list 319.4375 678.5893) 
(list 245.415 678.9393) 
(list 245.415 678.7623) 
(list 319.4375 678.5123)))
(apply 'command (append '("pline") coords '("c")))
(setq currobj (ssadd (entlast) currobj))
(setq coords (list 
(list 319.4375 678.3693) 
(list 245.415 678.6193) 
(list 245.415 678.4423) 
(list 319.4375 678.2923)))
(apply 'command (append '("pline") coords '("c")))
(setq currobj (ssadd (entlast) currobj))
(setq coords (list 
(list 319.4375 678.1493) 
(list 245.415 678.2993) 
(list 245.415 678.1223) 
(list 319.4375 678.0723)))
(apply 'command (append '("pline") coords '("c")))
(setq currobj (ssadd (entlast) currobj))
(setq coords (list 
(list 319.4375 677.9293) 
(list 245.415 677.9793) 
(list 245.415 677.8023) 
(list 319.4375 677.8523)))
(apply 'command (append '("pline") coords '("c")))
(setq currobj (ssadd (entlast) currobj))
(setq coords (list 
(list 319.4375 677.7093) 
(list 245.415 677.6593) 
(list 245.415 677.4823) 
(list 319.4375 677.6323)))
(apply 'command (append '("pline") coords '("c")))
(setq currobj (ssadd (entlast) currobj))
(setq coords (list 
(list 319.4375 677.4893) 
(list 245.415 677.3393) 
(list 245.415 677.1623) 
(list 319.4375 677.4123)))
(apply 'command (append '("pline") coords '("c")))
(setq currobj (ssadd (entlast) currobj))
(setq coords (list 
(list 319.4375 677.2693) 
(list 245.415 677.0193) 
(list 245.415 676.8423) 
(list 319.4375 677.1923)))
(apply 'command (append '("pline") coords '("c")))
(setq currobj (ssadd (entlast) currobj))
(setq coords (list 
(list 319.4375 677.0493) 
(list 245.415 676.6993) 
(list 245.415 676.5223) 
(list 319.4375 676.9723)))
(apply 'command (append '("pline") coords '("c")))
(setq currobj (ssadd (entlast) currobj))
(setq coords (list 
(list 319.4375 676.8293) 
(list 245.415 676.3793) 
(list 245.415 676.2023) 
(list 319.4375 676.7523)))
(apply 'command (append '("pline") coords '("c")))
(setq currobj (ssadd (entlast) currobj))
(setq coords (list 
(list 319.4375 676.6093) 
(list 245.415 676.0593) 
(list 245.415 675.8823) 
(list 319.4375 676.5323)))
(apply 'command (append '("pline") coords '("c")))
(setq currobj (ssadd (entlast) currobj))
(setq coords (list 
(list 319.4375 676.3893) 
(list 245.415 675.7393) 
(list 245.415 675.5623) 
(list 319.4375 676.3123)))
(apply 'command (append '("pline") coords '("c")))
(setq currobj (ssadd (entlast) currobj))
(command "_layer" "set" "nitride" "")
(command "_layer" "set" "text" "")
(command "_circle" "319.0625,665.1693" "0.075")
(command "_circle" "319.0625,665.4693" "0.075")
(command "_circle" "319.0625,665.7693" "0.075")
(command "_circle" "319.0625,666.0693" "0.075")
(command "_circle" "319.0625,666.3693" "0.075")
(command "_circle" "318.7625,665.1693" "0.075")
(command "_circle" "318.7625,665.4693" "0.075")
(command "_circle" "318.7625,665.7693" "0.075")
(command "_circle" "318.7625,666.0693" "0.075")
(command "_circle" "318.7625,666.3693" "0.075")
(command "_circle" "318.4625,665.1693" "0.075")
(command "_circle" "318.4625,665.4693" "0.075")
(command "_circle" "318.4625,665.7693" "0.075")
(command "_circle" "318.4625,666.0693" "0.075")
(command "_circle" "318.4625,666.3693" "0.075")
(command "_circle" "318.1625,665.1693" "0.075")
(command "_circle" "318.1625,665.4693" "0.075")
(command "_circle" "318.1625,665.7693" "0.075")
(command "_circle" "318.1625,666.0693" "0.075")
(command "_circle" "318.1625,666.3693" "0.075")
(command "_circle" "317.8625,665.1693" "0.075")
(command "_circle" "317.8625,665.4693" "0.075")
(command "_circle" "317.8625,665.7693" "0.075")
(command "_circle" "317.8625,666.0693" "0.075")
(command "_circle" "317.8625,666.3693" "0.075")
(command "_layer" "set" "nitride" "")
(setq coords (list 
(list 320.2625 690.6123) 
(list 320.2625 806.257) 
(list 319.7375 806.257) 
(list 319.7375 690.6123)))
(apply 'command (append '("pline") coords '("c")))
(setq currobj (ssadd (entlast) currobj))
(command "_layer" "set" "prebias" "")
(command "_rectangle" "319.7375,690.6123" "320.2625,806.257")
(setq currobj (ssadd (entlast) currobj))
(command "_layer" "set" "nitride" "")
(setq coords (list 
(list 320.2625 806.257) 
(list 320.5625 816.257) 
(list 320.5625 816.257) 
(list 320.5625 817.257) 
(list 394.585 816.507) 
(list 394.585 821.45) 
(list 320.5625 820.7) 
(list 320.5625 821.7) 
(list 320.5625 821.7) 
(list 320.2625 831.7) 
(list 319.7375 831.7) 
(list 319.4375 821.7) 
(list 319.4375 821.7) 
(list 319.4375 820.7) 
(list 245.415 821.45) 
(list 245.415 816.507) 
(list 319.4375 817.257) 
(list 319.4375 816.257) 
(list 319.4375 816.257) 
(list 319.7375 806.257)))
(apply 'command (append '("pline") coords '("c")))
(setq currobj (ssadd (entlast) currobj))
(command "_layer" "set" "prebias" "")
(setq coords (list 
(list 319.4375 806.257) 
(list 319.4375 817.257) 
(list 245.415 816.507) 
(list 245.415 821.45) 
(list 319.4375 820.7) 
(list 319.4375 831.7) 
(list 320.5625 831.7) 
(list 320.5625 820.7) 
(list 394.585 821.45) 
(list 394.585 816.507) 
(list 320.5625 817.257) 
(list 320.5625 806.257)))
(apply 'command (append '("pline") coords '("c")))
(setq currobj (ssadd (entlast) currobj))
(command "_layer" "set" "nitride" "")
(command "_layer" "set" "fda1" "")
(setq coords (list 
(list 320.5625 817.4) 
(list 394.585 816.65) 
(list 394.585 816.827) 
(list 320.5625 817.477)))
(apply 'command (append '("pline") coords '("c")))
(setq currobj (ssadd (entlast) currobj))
(setq coords (list 
(list 320.5625 817.62) 
(list 394.585 816.97) 
(list 394.585 817.147) 
(list 320.5625 817.697)))
(apply 'command (append '("pline") coords '("c")))
(setq currobj (ssadd (entlast) currobj))
(setq coords (list 
(list 320.5625 817.84) 
(list 394.585 817.29) 
(list 394.585 817.467) 
(list 320.5625 817.917)))
(apply 'command (append '("pline") coords '("c")))
(setq currobj (ssadd (entlast) currobj))
(setq coords (list 
(list 320.5625 818.06) 
(list 394.585 817.61) 
(list 394.585 817.787) 
(list 320.5625 818.137)))
(apply 'command (append '("pline") coords '("c")))
(setq currobj (ssadd (entlast) currobj))
(setq coords (list 
(list 320.5625 818.28) 
(list 394.585 817.93) 
(list 394.585 818.107) 
(list 320.5625 818.357)))
(apply 'command (append '("pline") coords '("c")))
(setq currobj (ssadd (entlast) currobj))
(setq coords (list 
(list 320.5625 818.5) 
(list 394.585 818.25) 
(list 394.585 818.427) 
(list 320.5625 818.577)))
(apply 'command (append '("pline") coords '("c")))
(setq currobj (ssadd (entlast) currobj))
(setq coords (list 
(list 320.5625 818.72) 
(list 394.585 818.57) 
(list 394.585 818.747) 
(list 320.5625 818.797)))
(apply 'command (append '("pline") coords '("c")))
(setq currobj (ssadd (entlast) currobj))
(setq coords (list 
(list 320.5625 818.94) 
(list 394.585 818.89) 
(list 394.585 819.067) 
(list 320.5625 819.017)))
(apply 'command (append '("pline") coords '("c")))
(setq currobj (ssadd (entlast) currobj))
(setq coords (list 
(list 320.5625 819.16) 
(list 394.585 819.21) 
(list 394.585 819.387) 
(list 320.5625 819.237)))
(apply 'command (append '("pline") coords '("c")))
(setq currobj (ssadd (entlast) currobj))
(setq coords (list 
(list 320.5625 819.38) 
(list 394.585 819.53) 
(list 394.585 819.707) 
(list 320.5625 819.457)))
(apply 'command (append '("pline") coords '("c")))
(setq currobj (ssadd (entlast) currobj))
(setq coords (list 
(list 320.5625 819.6) 
(list 394.585 819.85) 
(list 394.585 820.027) 
(list 320.5625 819.677)))
(apply 'command (append '("pline") coords '("c")))
(setq currobj (ssadd (entlast) currobj))
(setq coords (list 
(list 320.5625 819.82) 
(list 394.585 820.17) 
(list 394.585 820.347) 
(list 320.5625 819.897)))
(apply 'command (append '("pline") coords '("c")))
(setq currobj (ssadd (entlast) currobj))
(setq coords (list 
(list 320.5625 820.04) 
(list 394.585 820.49) 
(list 394.585 820.667) 
(list 320.5625 820.117)))
(apply 'command (append '("pline") coords '("c")))
(setq currobj (ssadd (entlast) currobj))
(setq coords (list 
(list 320.5625 820.26) 
(list 394.585 820.81) 
(list 394.585 820.987) 
(list 320.5625 820.337)))
(apply 'command (append '("pline") coords '("c")))
(setq currobj (ssadd (entlast) currobj))
(setq coords (list 
(list 320.5625 820.48) 
(list 394.585 821.13) 
(list 394.585 821.307) 
(list 320.5625 820.557)))
(apply 'command (append '("pline") coords '("c")))
(setq currobj (ssadd (entlast) currobj))
(setq coords (list 
(list 319.4375 820.557) 
(list 245.415 821.307) 
(list 245.415 821.13) 
(list 319.4375 820.48)))
(apply 'command (append '("pline") coords '("c")))
(setq currobj (ssadd (entlast) currobj))
(setq coords (list 
(list 319.4375 820.337) 
(list 245.415 820.987) 
(list 245.415 820.81) 
(list 319.4375 820.26)))
(apply 'command (append '("pline") coords '("c")))
(setq currobj (ssadd (entlast) currobj))
(setq coords (list 
(list 319.4375 820.117) 
(list 245.415 820.667) 
(list 245.415 820.49) 
(list 319.4375 820.04)))
(apply 'command (append '("pline") coords '("c")))
(setq currobj (ssadd (entlast) currobj))
(setq coords (list 
(list 319.4375 819.897) 
(list 245.415 820.347) 
(list 245.415 820.17) 
(list 319.4375 819.82)))
(apply 'command (append '("pline") coords '("c")))
(setq currobj (ssadd (entlast) currobj))
(setq coords (list 
(list 319.4375 819.677) 
(list 245.415 820.027) 
(list 245.415 819.85) 
(list 319.4375 819.6)))
(apply 'command (append '("pline") coords '("c")))
(setq currobj (ssadd (entlast) currobj))
(setq coords (list 
(list 319.4375 819.457) 
(list 245.415 819.707) 
(list 245.415 819.53) 
(list 319.4375 819.38)))
(apply 'command (append '("pline") coords '("c")))
(setq currobj (ssadd (entlast) currobj))
(setq coords (list 
(list 319.4375 819.237) 
(list 245.415 819.387) 
(list 245.415 819.21) 
(list 319.4375 819.16)))
(apply 'command (append '("pline") coords '("c")))
(setq currobj (ssadd (entlast) currobj))
(setq coords (list 
(list 319.4375 819.017) 
(list 245.415 819.067) 
(list 245.415 818.89) 
(list 319.4375 818.94)))
(apply 'command (append '("pline") coords '("c")))
(setq currobj (ssadd (entlast) currobj))
(setq coords (list 
(list 319.4375 818.797) 
(list 245.415 818.747) 
(list 245.415 818.57) 
(list 319.4375 818.72)))
(apply 'command (append '("pline") coords '("c")))
(setq currobj (ssadd (entlast) currobj))
(setq coords (list 
(list 319.4375 818.577) 
(list 245.415 818.427) 
(list 245.415 818.25) 
(list 319.4375 818.5)))
(apply 'command (append '("pline") coords '("c")))
(setq currobj (ssadd (entlast) currobj))
(setq coords (list 
(list 319.4375 818.357) 
(list 245.415 818.107) 
(list 245.415 817.93) 
(list 319.4375 818.28)))
(apply 'command (append '("pline") coords '("c")))
(setq currobj (ssadd (entlast) currobj))
(setq coords (list 
(list 319.4375 818.137) 
(list 245.415 817.787) 
(list 245.415 817.61) 
(list 319.4375 818.06)))
(apply 'command (append '("pline") coords '("c")))
(setq currobj (ssadd (entlast) currobj))
(setq coords (list 
(list 319.4375 817.917) 
(list 245.415 817.467) 
(list 245.415 817.29) 
(list 319.4375 817.84)))
(apply 'command (append '("pline") coords '("c")))
(setq currobj (ssadd (entlast) currobj))
(setq coords (list 
(list 319.4375 817.697) 
(list 245.415 817.147) 
(list 245.415 816.97) 
(list 319.4375 817.62)))
(apply 'command (append '("pline") coords '("c")))
(setq currobj (ssadd (entlast) currobj))
(setq coords (list 
(list 319.4375 817.477) 
(list 245.415 816.827) 
(list 245.415 816.65) 
(list 319.4375 817.4)))
(apply 'command (append '("pline") coords '("c")))
(setq currobj (ssadd (entlast) currobj))
(command "_layer" "set" "nitride" "")
(command "_layer" "set" "text" "")
(command "_circle" "319.0625,806.257" "0.075")
(command "_circle" "319.0625,806.557" "0.075")
(command "_circle" "319.0625,806.857" "0.075")
(command "_circle" "319.0625,807.157" "0.075")
(command "_circle" "319.0625,807.457" "0.075")
(command "_circle" "318.7625,806.257" "0.075")
(command "_circle" "318.7625,806.557" "0.075")
(command "_circle" "318.7625,806.857" "0.075")
(command "_circle" "318.7625,807.157" "0.075")
(command "_circle" "318.7625,807.457" "0.075")
(command "_circle" "318.4625,806.257" "0.075")
(command "_circle" "318.4625,806.557" "0.075")
(command "_circle" "318.4625,806.857" "0.075")
(command "_circle" "318.4625,807.157" "0.075")
(command "_circle" "318.4625,807.457" "0.075")
(command "_circle" "318.1625,806.257" "0.075")
(command "_circle" "318.1625,806.557" "0.075")
(command "_circle" "318.1625,806.857" "0.075")
(command "_circle" "318.1625,807.157" "0.075")
(command "_circle" "318.1625,807.457" "0.075")
(command "_circle" "317.8625,806.257" "0.075")
(command "_circle" "317.8625,806.557" "0.075")
(command "_circle" "317.8625,806.857" "0.075")
(command "_circle" "317.8625,807.157" "0.075")
(command "_circle" "317.8625,807.457" "0.075")
(command "_layer" "set" "nitride" "")
(setq coords (list 
(list 320.2625 831.7) 
(list 320.2625 836.7) 
(list 319.7375 836.7) 
(list 319.7375 831.7)))
(apply 'command (append '("pline") coords '("c")))
(setq currobj (ssadd (entlast) currobj))
(command "_layer" "set" "prebias" "")
(command "_rectangle" "319.7375,831.7" "320.2625,836.7")
(setq currobj (ssadd (entlast) currobj))
(command "_layer" "set" "nitride" "")
(setq cooledsinglenanobeam1 currobj)
(setq currobj nil)
(setq currobj (ssadd))
; DRAWING PHOTONIC CRYSTAL
(command "_layer" "set" "negYjunc" "")
(setq coords (list 
(list 320.135 866.7) 
(list 320 851.7) 
(list 320 866.7)))
(apply 'command (append '("pline") coords '("c")))
(setq currobj (ssadd (entlast) currobj))
(setq coords (list 
(list 320.2625 836.7) 
(list 320.415 866.7) 
(list 321.122 866.7) 
(list 321.122 836.7)))
(apply 'command (append '("pline") coords '("c")))
(setq currobj (ssadd (entlast) currobj))
(setq coords (list 
(list 319.865 866.7) 
(list 320 851.7) 
(list 320 866.7)))
(apply 'command (append '("pline") coords '("c")))
(setq currobj (ssadd (entlast) currobj))
(setq coords (list 
(list 319.7375 836.7) 
(list 319.585 866.7) 
(list 318.878 866.7) 
(list 318.878 836.7)))
(apply 'command (append '("pline") coords '("c")))
(setq currobj (ssadd (entlast) currobj))
(command "_layer" "set" "nitride" "")
(setq yjunction1 currobj)
(setq currobj nil)
(setq currobj (ssadd))
(setq tap1 nil)
(setq tap1 (ssadd))
(command "_layer" "set" "phc" "")
(setq coords (list 
(list 320 866.7) 
(list 320.135 866.7) 
(list 320.135 866.7103) 
(list 320.135 866.7206) 
(list 320.135 866.7308) 
(list 320.135 866.7411) 
(list 320.135 866.7514) 
(list 320.135 866.7617) 
(list 320.135 866.7719) 
(list 320.135 866.7822) 
(list 320.135 866.7925) 
(list 320.135 866.8028) 
(list 320.135 866.8131) 
(list 320.135 866.8233) 
(list 320.135 866.8336) 
(list 320.135 866.8439) 
(list 320.135 866.8542) 
(list 320.135 866.8644) 
(list 320.135 866.8747) 
(list 320.135 866.885) 
(list 320.135 866.8953) 
(list 320.135 866.9056) 
(list 320.135 866.9158) 
(list 320.135 866.9261) 
(list 320.135 866.9364) 
(list 320.135 866.9467) 
(list 320.135 866.9569) 
(list 320.135 866.9672) 
(list 320.135 866.9775) 
(list 320.135 866.9878) 
(list 320.135 866.9981) 
(list 320.135 867.0083) 
(list 320.135 867.0186) 
(list 320.135 867.0289) 
(list 320.135 867.0392) 
(list 320.135 867.0494) 
(list 320.135 867.0597) 
(list 320.135 867.07) 
(list 320 867.07)))
(apply 'command (append '("pline") coords '("c")))
(setq tap1 (ssadd (entlast) tap1))
(command "_mirror" (entlast) "" "320,900" "320,901" "No")
(setq tap1 (ssadd (entlast) tap1))
(setq coords (list 
(list 320.4247 866.7) 
(list 320.415 866.7) 
(list 320.4153 866.7103) 
(list 320.4155 866.7206) 
(list 320.4157 866.7308) 
(list 320.4158 866.7411) 
(list 320.4159 866.7514) 
(list 320.4159 866.7617) 
(list 320.4158 866.7719) 
(list 320.4155 866.7822) 
(list 320.4152 866.7925) 
(list 320.4148 866.8028) 
(list 320.4143 866.8131) 
(list 320.4138 866.8233) 
(list 320.4132 866.8336) 
(list 320.4126 866.8439) 
(list 320.4121 866.8542) 
(list 320.4116 866.8644) 
(list 320.4112 866.8747) 
(list 320.4109 866.885) 
(list 320.4108 866.8953) 
(list 320.4108 866.9056) 
(list 320.411 866.9158) 
(list 320.4113 866.9261) 
(list 320.4118 866.9364) 
(list 320.4126 866.9467) 
(list 320.4134 866.9569) 
(list 320.4145 866.9672) 
(list 320.4156 866.9775) 
(list 320.4168 866.9878) 
(list 320.4181 866.9981) 
(list 320.4194 867.0083) 
(list 320.4206 867.0186) 
(list 320.4218 867.0289) 
(list 320.4228 867.0392) 
(list 320.4237 867.0494) 
(list 320.4243 867.0597) 
(list 320.4247 867.07) 
(list 320.4247 867.07)))
(apply 'command (append '("pline") coords '("c")))
(setq tap1 (ssadd (entlast) tap1))
(command "_mirror" (entlast) "" "320,900" "320,901" "No")
(setq tap1 (ssadd (entlast) tap1))
(setq coords (list 
(list 321.122 866.7) 
(list 320.4247 866.7) 
(list 320.4247 866.7103) 
(list 320.4247 866.7206) 
(list 320.4247 866.7308) 
(list 320.4247 866.7411) 
(list 320.4247 866.7514) 
(list 320.4247 866.7617) 
(list 320.4247 866.7719) 
(list 320.4247 866.7822) 
(list 320.4247 866.7925) 
(list 320.4247 866.8028) 
(list 320.4247 866.8131) 
(list 320.4247 866.8233) 
(list 320.4247 866.8336) 
(list 320.4247 866.8439) 
(list 320.4247 866.8542) 
(list 320.4247 866.8644) 
(list 320.4247 866.8747) 
(list 320.4247 866.885) 
(list 320.4247 866.8953) 
(list 320.4247 866.9056) 
(list 320.4247 866.9158) 
(list 320.4247 866.9261) 
(list 320.4247 866.9364) 
(list 320.4247 866.9467) 
(list 320.4247 866.9569) 
(list 320.4247 866.9672) 
(list 320.4247 866.9775) 
(list 320.4247 866.9878) 
(list 320.4247 866.9981) 
(list 320.4247 867.0083) 
(list 320.4247 867.0186) 
(list 320.4247 867.0289) 
(list 320.4247 867.0392) 
(list 320.4247 867.0494) 
(list 320.4247 867.0597) 
(list 320.4247 867.07) 
(list 321.122 867.07)))
(apply 'command (append '("pline") coords '("c")))
(setq tap1 (ssadd (entlast) tap1))
(command "_mirror" (entlast) "" "320,900" "320,901" "No")
(setq tap1 (ssadd (entlast) tap1))
(setq coords (list 
(list 320 867.07) 
(list 320.135 867.07) 
(list 320.135 867.0803) 
(list 320.135 867.0906) 
(list 320.135 867.1008) 
(list 320.135 867.1111) 
(list 320.135 867.1214) 
(list 320.135 867.1317) 
(list 320.135 867.1419) 
(list 320.135 867.1522) 
(list 320.135 867.1625) 
(list 320.135 867.1728) 
(list 320.135 867.1831) 
(list 320.135 867.1933) 
(list 320.135 867.2036) 
(list 320.135 867.2139) 
(list 320.135 867.2242) 
(list 320.135 867.2344) 
(list 320.135 867.2447) 
(list 320.135 867.255) 
(list 320.135 867.2653) 
(list 320.135 867.2756) 
(list 320.135 867.2858) 
(list 320.135 867.2961) 
(list 320.135 867.3064) 
(list 320.135 867.3167) 
(list 320.135 867.3269) 
(list 320.135 867.3372) 
(list 320.135 867.3475) 
(list 320.135 867.3578) 
(list 320.135 867.3681) 
(list 320.135 867.3783) 
(list 320.135 867.3886) 
(list 320.135 867.3989) 
(list 320.135 867.4092) 
(list 320.135 867.4194) 
(list 320.135 867.4297) 
(list 320.135 867.44) 
(list 320 867.44)))
(apply 'command (append '("pline") coords '("c")))
(setq tap1 (ssadd (entlast) tap1))
(command "_mirror" (entlast) "" "320,900" "320,901" "No")
(setq tap1 (ssadd (entlast) tap1))
(setq coords (list 
(list 320.4345 867.07) 
(list 320.4247 867.07) 
(list 320.4249 867.0803) 
(list 320.4247 867.0906) 
(list 320.4242 867.1008) 
(list 320.4235 867.1111) 
(list 320.4225 867.1214) 
(list 320.4211 867.1317) 
(list 320.4196 867.1419) 
(list 320.4179 867.1522) 
(list 320.416 867.1625) 
(list 320.414 867.1728) 
(list 320.4121 867.1831) 
(list 320.4101 867.1933) 
(list 320.4083 867.2036) 
(list 320.4066 867.2139) 
(list 320.4052 867.2242) 
(list 320.404 867.2344) 
(list 320.4032 867.2447) 
(list 320.4028 867.255) 
(list 320.4028 867.2653) 
(list 320.4032 867.2756) 
(list 320.404 867.2858) 
(list 320.4053 867.2961) 
(list 320.4069 867.3064) 
(list 320.4089 867.3167) 
(list 320.4112 867.3269) 
(list 320.4137 867.3372) 
(list 320.4164 867.3475) 
(list 320.4192 867.3578) 
(list 320.422 867.3681) 
(list 320.4247 867.3783) 
(list 320.4272 867.3886) 
(list 320.4294 867.3989) 
(list 320.4314 867.4092) 
(list 320.4329 867.4194) 
(list 320.4339 867.4297) 
(list 320.4345 867.44) 
(list 320.4345 867.44)))
(apply 'command (append '("pline") coords '("c")))
(setq tap1 (ssadd (entlast) tap1))
(command "_mirror" (entlast) "" "320,900" "320,901" "No")
(setq tap1 (ssadd (entlast) tap1))
(setq coords (list 
(list 321.122 867.07) 
(list 320.4345 867.07) 
(list 320.4345 867.0803) 
(list 320.4345 867.0906) 
(list 320.4345 867.1008) 
(list 320.4345 867.1111) 
(list 320.4345 867.1214) 
(list 320.4345 867.1317) 
(list 320.4345 867.1419) 
(list 320.4345 867.1522) 
(list 320.4345 867.1625) 
(list 320.4345 867.1728) 
(list 320.4345 867.1831) 
(list 320.4345 867.1933) 
(list 320.4345 867.2036) 
(list 320.4345 867.2139) 
(list 320.4345 867.2242) 
(list 320.4345 867.2344) 
(list 320.4345 867.2447) 
(list 320.4345 867.255) 
(list 320.4345 867.2653) 
(list 320.4345 867.2756) 
(list 320.4345 867.2858) 
(list 320.4345 867.2961) 
(list 320.4345 867.3064) 
(list 320.4345 867.3167) 
(list 320.4345 867.3269) 
(list 320.4345 867.3372) 
(list 320.4345 867.3475) 
(list 320.4345 867.3578) 
(list 320.4345 867.3681) 
(list 320.4345 867.3783) 
(list 320.4345 867.3886) 
(list 320.4345 867.3989) 
(list 320.4345 867.4092) 
(list 320.4345 867.4194) 
(list 320.4345 867.4297) 
(list 320.4345 867.44) 
(list 321.122 867.44)))
(apply 'command (append '("pline") coords '("c")))
(setq tap1 (ssadd (entlast) tap1))
(command "_mirror" (entlast) "" "320,900" "320,901" "No")
(setq tap1 (ssadd (entlast) tap1))
(setq coords (list 
(list 320 867.44) 
(list 320.135 867.44) 
(list 320.135 867.4503) 
(list 320.135 867.4606) 
(list 320.135 867.4708) 
(list 320.135 867.4811) 
(list 320.135 867.4914) 
(list 320.135 867.5017) 
(list 320.135 867.5119) 
(list 320.135 867.5222) 
(list 320.135 867.5325) 
(list 320.135 867.5428) 
(list 320.135 867.5531) 
(list 320.135 867.5633) 
(list 320.135 867.5736) 
(list 320.135 867.5839) 
(list 320.135 867.5942) 
(list 320.135 867.6044) 
(list 320.135 867.6147) 
(list 320.135 867.625) 
(list 320.135 867.6353) 
(list 320.135 867.6456) 
(list 320.135 867.6558) 
(list 320.135 867.6661) 
(list 320.135 867.6764) 
(list 320.135 867.6867) 
(list 320.135 867.6969) 
(list 320.135 867.7072) 
(list 320.135 867.7175) 
(list 320.135 867.7278) 
(list 320.135 867.7381) 
(list 320.135 867.7483) 
(list 320.135 867.7586) 
(list 320.135 867.7689) 
(list 320.135 867.7792) 
(list 320.135 867.7894) 
(list 320.135 867.7997) 
(list 320.135 867.81) 
(list 320 867.81)))
(apply 'command (append '("pline") coords '("c")))
(setq tap1 (ssadd (entlast) tap1))
(command "_mirror" (entlast) "" "320,900" "320,901" "No")
(setq tap1 (ssadd (entlast) tap1))
(setq coords (list 
(list 320.4442 867.44) 
(list 320.4345 867.44) 
(list 320.4345 867.4503) 
(list 320.4339 867.4606) 
(list 320.4328 867.4708) 
(list 320.4311 867.4811) 
(list 320.429 867.4914) 
(list 320.4264 867.5017) 
(list 320.4235 867.5119) 
(list 320.4202 867.5222) 
(list 320.4168 867.5325) 
(list 320.4133 867.5428) 
(list 320.4098 867.5531) 
(list 320.4064 867.5633) 
(list 320.4033 867.5736) 
(list 320.4006 867.5839) 
(list 320.3982 867.5942) 
(list 320.3964 867.6044) 
(list 320.3952 867.6147) 
(list 320.3947 867.625) 
(list 320.3948 867.6353) 
(list 320.3956 867.6456) 
(list 320.3971 867.6558) 
(list 320.3992 867.6661) 
(list 320.402 867.6764) 
(list 320.4052 867.6867) 
(list 320.4089 867.6969) 
(list 320.413 867.7072) 
(list 320.4172 867.7175) 
(list 320.4215 867.7278) 
(list 320.4258 867.7381) 
(list 320.4299 867.7483) 
(list 320.4337 867.7586) 
(list 320.4371 867.7689) 
(list 320.4399 867.7792) 
(list 320.4421 867.7894) 
(list 320.4435 867.7997) 
(list 320.4442 867.81) 
(list 320.4442 867.81)))
(apply 'command (append '("pline") coords '("c")))
(setq tap1 (ssadd (entlast) tap1))
(command "_mirror" (entlast) "" "320,900" "320,901" "No")
(setq tap1 (ssadd (entlast) tap1))
(setq coords (list 
(list 321.122 867.44) 
(list 320.4442 867.44) 
(list 320.4442 867.4503) 
(list 320.4442 867.4606) 
(list 320.4442 867.4708) 
(list 320.4442 867.4811) 
(list 320.4442 867.4914) 
(list 320.4442 867.5017) 
(list 320.4442 867.5119) 
(list 320.4442 867.5222) 
(list 320.4442 867.5325) 
(list 320.4442 867.5428) 
(list 320.4442 867.5531) 
(list 320.4442 867.5633) 
(list 320.4442 867.5736) 
(list 320.4442 867.5839) 
(list 320.4442 867.5942) 
(list 320.4442 867.6044) 
(list 320.4442 867.6147) 
(list 320.4442 867.625) 
(list 320.4442 867.6353) 
(list 320.4442 867.6456) 
(list 320.4442 867.6558) 
(list 320.4442 867.6661) 
(list 320.4442 867.6764) 
(list 320.4442 867.6867) 
(list 320.4442 867.6969) 
(list 320.4442 867.7072) 
(list 320.4442 867.7175) 
(list 320.4442 867.7278) 
(list 320.4442 867.7381) 
(list 320.4442 867.7483) 
(list 320.4442 867.7586) 
(list 320.4442 867.7689) 
(list 320.4442 867.7792) 
(list 320.4442 867.7894) 
(list 320.4442 867.7997) 
(list 320.4442 867.81) 
(list 321.122 867.81)))
(apply 'command (append '("pline") coords '("c")))
(setq tap1 (ssadd (entlast) tap1))
(command "_mirror" (entlast) "" "320,900" "320,901" "No")
(setq tap1 (ssadd (entlast) tap1))
(setq coords (list 
(list 320 867.81) 
(list 320.135 867.81) 
(list 320.135 867.8203) 
(list 320.135 867.8306) 
(list 320.135 867.8408) 
(list 320.135 867.8511) 
(list 320.135 867.8614) 
(list 320.135 867.8717) 
(list 320.135 867.8819) 
(list 320.135 867.8922) 
(list 320.135 867.9025) 
(list 320.135 867.9128) 
(list 320.135 867.9231) 
(list 320.135 867.9333) 
(list 320.135 867.9436) 
(list 320.135 867.9539) 
(list 320.135 867.9642) 
(list 320.135 867.9744) 
(list 320.135 867.9847) 
(list 320.135 867.995) 
(list 320.135 868.0053) 
(list 320.135 868.0156) 
(list 320.135 868.0258) 
(list 320.135 868.0361) 
(list 320.135 868.0464) 
(list 320.135 868.0567) 
(list 320.135 868.0669) 
(list 320.135 868.0772) 
(list 320.135 868.0875) 
(list 320.135 868.0978) 
(list 320.135 868.1081) 
(list 320.135 868.1183) 
(list 320.135 868.1286) 
(list 320.135 868.1389) 
(list 320.135 868.1492) 
(list 320.135 868.1594) 
(list 320.135 868.1697) 
(list 320.135 868.18) 
(list 320 868.18)))
(apply 'command (append '("pline") coords '("c")))
(setq tap1 (ssadd (entlast) tap1))
(command "_mirror" (entlast) "" "320,900" "320,901" "No")
(setq tap1 (ssadd (entlast) tap1))
(setq coords (list 
(list 320.4539 867.81) 
(list 320.4442 867.81) 
(list 320.4441 867.8203) 
(list 320.4431 867.8306) 
(list 320.4413 867.8408) 
(list 320.4388 867.8511) 
(list 320.4355 867.8614) 
(list 320.4317 867.8717) 
(list 320.4273 867.8819) 
(list 320.4226 867.8922) 
(list 320.4176 867.9025) 
(list 320.4125 867.9128) 
(list 320.4075 867.9231) 
(list 320.4028 867.9333) 
(list 320.3984 867.9436) 
(list 320.3945 867.9539) 
(list 320.3913 867.9642) 
(list 320.3888 867.9744) 
(list 320.3872 867.9847) 
(list 320.3865 867.995) 
(list 320.3868 868.0053) 
(list 320.388 868.0156) 
(list 320.3901 868.0258) 
(list 320.3932 868.0361) 
(list 320.397 868.0464) 
(list 320.4016 868.0567) 
(list 320.4067 868.0669) 
(list 320.4122 868.0772) 
(list 320.418 868.0875) 
(list 320.4239 868.0978) 
(list 320.4297 868.1081) 
(list 320.4352 868.1183) 
(list 320.4403 868.1286) 
(list 320.4447 868.1389) 
(list 320.4484 868.1492) 
(list 320.4513 868.1594) 
(list 320.4531 868.1697) 
(list 320.4539 868.18) 
(list 320.4539 868.18)))
(apply 'command (append '("pline") coords '("c")))
(setq tap1 (ssadd (entlast) tap1))
(command "_mirror" (entlast) "" "320,900" "320,901" "No")
(setq tap1 (ssadd (entlast) tap1))
(setq coords (list 
(list 321.122 867.81) 
(list 320.4539 867.81) 
(list 320.4539 867.8203) 
(list 320.4539 867.8306) 
(list 320.4539 867.8408) 
(list 320.4539 867.8511) 
(list 320.4539 867.8614) 
(list 320.4539 867.8717) 
(list 320.4539 867.8819) 
(list 320.4539 867.8922) 
(list 320.4539 867.9025) 
(list 320.4539 867.9128) 
(list 320.4539 867.9231) 
(list 320.4539 867.9333) 
(list 320.4539 867.9436) 
(list 320.4539 867.9539) 
(list 320.4539 867.9642) 
(list 320.4539 867.9744) 
(list 320.4539 867.9847) 
(list 320.4539 867.995) 
(list 320.4539 868.0053) 
(list 320.4539 868.0156) 
(list 320.4539 868.0258) 
(list 320.4539 868.0361) 
(list 320.4539 868.0464) 
(list 320.4539 868.0567) 
(list 320.4539 868.0669) 
(list 320.4539 868.0772) 
(list 320.4539 868.0875) 
(list 320.4539 868.0978) 
(list 320.4539 868.1081) 
(list 320.4539 868.1183) 
(list 320.4539 868.1286) 
(list 320.4539 868.1389) 
(list 320.4539 868.1492) 
(list 320.4539 868.1594) 
(list 320.4539 868.1697) 
(list 320.4539 868.18) 
(list 321.122 868.18)))
(apply 'command (append '("pline") coords '("c")))
(setq tap1 (ssadd (entlast) tap1))
(command "_mirror" (entlast) "" "320,900" "320,901" "No")
(setq tap1 (ssadd (entlast) tap1))
(setq coords (list 
(list 320 868.18) 
(list 320.135 868.18) 
(list 320.135 868.1903) 
(list 320.135 868.2006) 
(list 320.135 868.2108) 
(list 320.135 868.2211) 
(list 320.135 868.2314) 
(list 320.135 868.2417) 
(list 320.135 868.2519) 
(list 320.135 868.2622) 
(list 320.135 868.2725) 
(list 320.135 868.2828) 
(list 320.135 868.2931) 
(list 320.135 868.3033) 
(list 320.135 868.3136) 
(list 320.135 868.3239) 
(list 320.135 868.3342) 
(list 320.135 868.3444) 
(list 320.135 868.3547) 
(list 320.135 868.365) 
(list 320.135 868.3753) 
(list 320.135 868.3856) 
(list 320.135 868.3958) 
(list 320.135 868.4061) 
(list 320.135 868.4164) 
(list 320.135 868.4267) 
(list 320.135 868.4369) 
(list 320.135 868.4472) 
(list 320.135 868.4575) 
(list 320.135 868.4678) 
(list 320.135 868.4781) 
(list 320.135 868.4883) 
(list 320.135 868.4986) 
(list 320.135 868.5089) 
(list 320.135 868.5192) 
(list 320.135 868.5294) 
(list 320.135 868.5397) 
(list 320.135 868.55) 
(list 320 868.55)))
(apply 'command (append '("pline") coords '("c")))
(setq tap1 (ssadd (entlast) tap1))
(command "_mirror" (entlast) "" "320,900" "320,901" "No")
(setq tap1 (ssadd (entlast) tap1))
(setq coords (list 
(list 320.4637 868.18) 
(list 320.4539 868.18) 
(list 320.4537 868.1903) 
(list 320.4523 868.2006) 
(list 320.4499 868.2108) 
(list 320.4464 868.2211) 
(list 320.4421 868.2314) 
(list 320.4369 868.2417) 
(list 320.4312 868.2519) 
(list 320.4249 868.2622) 
(list 320.4184 868.2725) 
(list 320.4118 868.2828) 
(list 320.4053 868.2931) 
(list 320.3991 868.3033) 
(list 320.3934 868.3136) 
(list 320.3885 868.3239) 
(list 320.3844 868.3342) 
(list 320.3812 868.3444) 
(list 320.3792 868.3547) 
(list 320.3784 868.365) 
(list 320.3788 868.3753) 
(list 320.3804 868.3856) 
(list 320.3832 868.3958) 
(list 320.3871 868.4061) 
(list 320.3921 868.4164) 
(list 320.3979 868.4267) 
(list 320.4044 868.4369) 
(list 320.4115 868.4472) 
(list 320.4188 868.4575) 
(list 320.4262 868.4678) 
(list 320.4335 868.4781) 
(list 320.4405 868.4883) 
(list 320.4468 868.4986) 
(list 320.4524 868.5089) 
(list 320.457 868.5192) 
(list 320.4605 868.5294) 
(list 320.4627 868.5397) 
(list 320.4637 868.55) 
(list 320.4637 868.55)))
(apply 'command (append '("pline") coords '("c")))
(setq tap1 (ssadd (entlast) tap1))
(command "_mirror" (entlast) "" "320,900" "320,901" "No")
(setq tap1 (ssadd (entlast) tap1))
(setq coords (list 
(list 321.122 868.18) 
(list 320.4637 868.18) 
(list 320.4637 868.1903) 
(list 320.4637 868.2006) 
(list 320.4637 868.2108) 
(list 320.4637 868.2211) 
(list 320.4637 868.2314) 
(list 320.4637 868.2417) 
(list 320.4637 868.2519) 
(list 320.4637 868.2622) 
(list 320.4637 868.2725) 
(list 320.4637 868.2828) 
(list 320.4637 868.2931) 
(list 320.4637 868.3033) 
(list 320.4637 868.3136) 
(list 320.4637 868.3239) 
(list 320.4637 868.3342) 
(list 320.4637 868.3444) 
(list 320.4637 868.3547) 
(list 320.4637 868.365) 
(list 320.4637 868.3753) 
(list 320.4637 868.3856) 
(list 320.4637 868.3958) 
(list 320.4637 868.4061) 
(list 320.4637 868.4164) 
(list 320.4637 868.4267) 
(list 320.4637 868.4369) 
(list 320.4637 868.4472) 
(list 320.4637 868.4575) 
(list 320.4637 868.4678) 
(list 320.4637 868.4781) 
(list 320.4637 868.4883) 
(list 320.4637 868.4986) 
(list 320.4637 868.5089) 
(list 320.4637 868.5192) 
(list 320.4637 868.5294) 
(list 320.4637 868.5397) 
(list 320.4637 868.55) 
(list 321.122 868.55)))
(apply 'command (append '("pline") coords '("c")))
(setq tap1 (ssadd (entlast) tap1))
(command "_mirror" (entlast) "" "320,900" "320,901" "No")
(setq tap1 (ssadd (entlast) tap1))
(setq coords (list 
(list 320 868.55) 
(list 320.135 868.55) 
(list 320.135 868.5603) 
(list 320.135 868.5706) 
(list 320.135 868.5808) 
(list 320.135 868.5911) 
(list 320.135 868.6014) 
(list 320.135 868.6117) 
(list 320.135 868.6219) 
(list 320.135 868.6322) 
(list 320.135 868.6425) 
(list 320.135 868.6528) 
(list 320.135 868.6631) 
(list 320.135 868.6733) 
(list 320.135 868.6836) 
(list 320.135 868.6939) 
(list 320.135 868.7042) 
(list 320.135 868.7144) 
(list 320.135 868.7247) 
(list 320.135 868.735) 
(list 320.135 868.7453) 
(list 320.135 868.7556) 
(list 320.135 868.7658) 
(list 320.135 868.7761) 
(list 320.135 868.7864) 
(list 320.135 868.7967) 
(list 320.135 868.8069) 
(list 320.135 868.8172) 
(list 320.135 868.8275) 
(list 320.135 868.8378) 
(list 320.135 868.8481) 
(list 320.135 868.8583) 
(list 320.135 868.8686) 
(list 320.135 868.8789) 
(list 320.135 868.8892) 
(list 320.135 868.8994) 
(list 320.135 868.9097) 
(list 320.135 868.92) 
(list 320 868.92)))
(apply 'command (append '("pline") coords '("c")))
(setq tap1 (ssadd (entlast) tap1))
(command "_mirror" (entlast) "" "320,900" "320,901" "No")
(setq tap1 (ssadd (entlast) tap1))
(setq coords (list 
(list 320.4734 868.55) 
(list 320.4637 868.55) 
(list 320.4633 868.5603) 
(list 320.4615 868.5706) 
(list 320.4584 868.5808) 
(list 320.4541 868.5911) 
(list 320.4486 868.6014) 
(list 320.4422 868.6117) 
(list 320.435 868.6219) 
(list 320.4273 868.6322) 
(list 320.4192 868.6425) 
(list 320.411 868.6528) 
(list 320.403 868.6631) 
(list 320.3954 868.6733) 
(list 320.3885 868.6836) 
(list 320.3824 868.6939) 
(list 320.3774 868.7042) 
(list 320.3737 868.7144) 
(list 320.3712 868.7247) 
(list 320.3703 868.735) 
(list 320.3708 868.7453) 
(list 320.3728 868.7556) 
(list 320.3763 868.7658) 
(list 320.3811 868.7761) 
(list 320.3871 868.7864) 
(list 320.3942 868.7967) 
(list 320.4022 868.8069) 
(list 320.4107 868.8172) 
(list 320.4196 868.8275) 
(list 320.4286 868.8378) 
(list 320.4374 868.8481) 
(list 320.4457 868.8583) 
(list 320.4533 868.8686) 
(list 320.46 868.8789) 
(list 320.4655 868.8892) 
(list 320.4697 868.8994) 
(list 320.4723 868.9097) 
(list 320.4734 868.92) 
(list 320.4734 868.92)))
(apply 'command (append '("pline") coords '("c")))
(setq tap1 (ssadd (entlast) tap1))
(command "_mirror" (entlast) "" "320,900" "320,901" "No")
(setq tap1 (ssadd (entlast) tap1))
(setq coords (list 
(list 321.122 868.55) 
(list 320.4734 868.55) 
(list 320.4734 868.5603) 
(list 320.4734 868.5706) 
(list 320.4734 868.5808) 
(list 320.4734 868.5911) 
(list 320.4734 868.6014) 
(list 320.4734 868.6117) 
(list 320.4734 868.6219) 
(list 320.4734 868.6322) 
(list 320.4734 868.6425) 
(list 320.4734 868.6528) 
(list 320.4734 868.6631) 
(list 320.4734 868.6733) 
(list 320.4734 868.6836) 
(list 320.4734 868.6939) 
(list 320.4734 868.7042) 
(list 320.4734 868.7144) 
(list 320.4734 868.7247) 
(list 320.4734 868.735) 
(list 320.4734 868.7453) 
(list 320.4734 868.7556) 
(list 320.4734 868.7658) 
(list 320.4734 868.7761) 
(list 320.4734 868.7864) 
(list 320.4734 868.7967) 
(list 320.4734 868.8069) 
(list 320.4734 868.8172) 
(list 320.4734 868.8275) 
(list 320.4734 868.8378) 
(list 320.4734 868.8481) 
(list 320.4734 868.8583) 
(list 320.4734 868.8686) 
(list 320.4734 868.8789) 
(list 320.4734 868.8892) 
(list 320.4734 868.8994) 
(list 320.4734 868.9097) 
(list 320.4734 868.92) 
(list 321.122 868.92)))
(apply 'command (append '("pline") coords '("c")))
(setq tap1 (ssadd (entlast) tap1))
(command "_mirror" (entlast) "" "320,900" "320,901" "No")
(setq tap1 (ssadd (entlast) tap1))
(setq coords (list 
(list 320 868.92) 
(list 320.135 868.92) 
(list 320.135 868.9303) 
(list 320.135 868.9406) 
(list 320.135 868.9508) 
(list 320.135 868.9611) 
(list 320.135 868.9714) 
(list 320.135 868.9817) 
(list 320.135 868.9919) 
(list 320.135 869.0022) 
(list 320.135 869.0125) 
(list 320.135 869.0228) 
(list 320.135 869.0331) 
(list 320.135 869.0433) 
(list 320.135 869.0536) 
(list 320.135 869.0639) 
(list 320.135 869.0742) 
(list 320.135 869.0844) 
(list 320.135 869.0947) 
(list 320.135 869.105) 
(list 320.135 869.1153) 
(list 320.135 869.1256) 
(list 320.135 869.1358) 
(list 320.135 869.1461) 
(list 320.135 869.1564) 
(list 320.135 869.1667) 
(list 320.135 869.1769) 
(list 320.135 869.1872) 
(list 320.135 869.1975) 
(list 320.135 869.2078) 
(list 320.135 869.2181) 
(list 320.135 869.2283) 
(list 320.135 869.2386) 
(list 320.135 869.2489) 
(list 320.135 869.2592) 
(list 320.135 869.2694) 
(list 320.135 869.2797) 
(list 320.135 869.29) 
(list 320 869.29)))
(apply 'command (append '("pline") coords '("c")))
(setq tap1 (ssadd (entlast) tap1))
(command "_mirror" (entlast) "" "320,900" "320,901" "No")
(setq tap1 (ssadd (entlast) tap1))
(setq coords (list 
(list 320.4831 868.92) 
(list 320.4734 868.92) 
(list 320.4729 868.9303) 
(list 320.4707 868.9406) 
(list 320.4669 868.9508) 
(list 320.4617 868.9611) 
(list 320.4552 868.9714) 
(list 320.4475 868.9817) 
(list 320.4389 868.9919) 
(list 320.4296 869.0022) 
(list 320.42 869.0125) 
(list 320.4103 869.0228) 
(list 320.4008 869.0331) 
(list 320.3918 869.0433) 
(list 320.3836 869.0536) 
(list 320.3764 869.0639) 
(list 320.3705 869.0742) 
(list 320.3661 869.0844) 
(list 320.3632 869.0947) 
(list 320.3621 869.105) 
(list 320.3628 869.1153) 
(list 320.3652 869.1256) 
(list 320.3693 869.1358) 
(list 320.375 869.1461) 
(list 320.3822 869.1564) 
(list 320.3906 869.1667) 
(list 320.3999 869.1769) 
(list 320.4099 869.1872) 
(list 320.4204 869.1975) 
(list 320.4309 869.2078) 
(list 320.4412 869.2181) 
(list 320.451 869.2283) 
(list 320.4599 869.2386) 
(list 320.4677 869.2489) 
(list 320.474 869.2592) 
(list 320.4789 869.2694) 
(list 320.4819 869.2797) 
(list 320.4831 869.29) 
(list 320.4831 869.29)))
(apply 'command (append '("pline") coords '("c")))
(setq tap1 (ssadd (entlast) tap1))
(command "_mirror" (entlast) "" "320,900" "320,901" "No")
(setq tap1 (ssadd (entlast) tap1))
(setq coords (list 
(list 321.122 868.92) 
(list 320.4831 868.92) 
(list 320.4831 868.9303) 
(list 320.4831 868.9406) 
(list 320.4831 868.9508) 
(list 320.4831 868.9611) 
(list 320.4831 868.9714) 
(list 320.4831 868.9817) 
(list 320.4831 868.9919) 
(list 320.4831 869.0022) 
(list 320.4831 869.0125) 
(list 320.4831 869.0228) 
(list 320.4831 869.0331) 
(list 320.4831 869.0433) 
(list 320.4831 869.0536) 
(list 320.4831 869.0639) 
(list 320.4831 869.0742) 
(list 320.4831 869.0844) 
(list 320.4831 869.0947) 
(list 320.4831 869.105) 
(list 320.4831 869.1153) 
(list 320.4831 869.1256) 
(list 320.4831 869.1358) 
(list 320.4831 869.1461) 
(list 320.4831 869.1564) 
(list 320.4831 869.1667) 
(list 320.4831 869.1769) 
(list 320.4831 869.1872) 
(list 320.4831 869.1975) 
(list 320.4831 869.2078) 
(list 320.4831 869.2181) 
(list 320.4831 869.2283) 
(list 320.4831 869.2386) 
(list 320.4831 869.2489) 
(list 320.4831 869.2592) 
(list 320.4831 869.2694) 
(list 320.4831 869.2797) 
(list 320.4831 869.29) 
(list 321.122 869.29)))
(apply 'command (append '("pline") coords '("c")))
(setq tap1 (ssadd (entlast) tap1))
(command "_mirror" (entlast) "" "320,900" "320,901" "No")
(setq tap1 (ssadd (entlast) tap1))
(setq coords (list 
(list 320 869.29) 
(list 320.135 869.29) 
(list 320.135 869.3003) 
(list 320.135 869.3106) 
(list 320.135 869.3208) 
(list 320.135 869.3311) 
(list 320.135 869.3414) 
(list 320.135 869.3517) 
(list 320.135 869.3619) 
(list 320.135 869.3722) 
(list 320.135 869.3825) 
(list 320.135 869.3928) 
(list 320.135 869.4031) 
(list 320.135 869.4133) 
(list 320.135 869.4236) 
(list 320.135 869.4339) 
(list 320.135 869.4442) 
(list 320.135 869.4544) 
(list 320.135 869.4647) 
(list 320.135 869.475) 
(list 320.135 869.4853) 
(list 320.135 869.4956) 
(list 320.135 869.5058) 
(list 320.135 869.5161) 
(list 320.135 869.5264) 
(list 320.135 869.5367) 
(list 320.135 869.5469) 
(list 320.135 869.5572) 
(list 320.135 869.5675) 
(list 320.135 869.5778) 
(list 320.135 869.5881) 
(list 320.135 869.5983) 
(list 320.135 869.6086) 
(list 320.135 869.6189) 
(list 320.135 869.6292) 
(list 320.135 869.6394) 
(list 320.135 869.6497) 
(list 320.135 869.66) 
(list 320 869.66)))
(apply 'command (append '("pline") coords '("c")))
(setq tap1 (ssadd (entlast) tap1))
(command "_mirror" (entlast) "" "320,900" "320,901" "No")
(setq tap1 (ssadd (entlast) tap1))
(setq coords (list 
(list 320.4929 869.29) 
(list 320.4831 869.29) 
(list 320.4824 869.3003) 
(list 320.4799 869.3106) 
(list 320.4755 869.3208) 
(list 320.4694 869.3311) 
(list 320.4617 869.3414) 
(list 320.4527 869.3517) 
(list 320.4427 869.3619) 
(list 320.432 869.3722) 
(list 320.4208 869.3825) 
(list 320.4095 869.3928) 
(list 320.3985 869.4031) 
(list 320.3881 869.4133) 
(list 320.3786 869.4236) 
(list 320.3703 869.4339) 
(list 320.3636 869.4442) 
(list 320.3585 869.4544) 
(list 320.3552 869.4647) 
(list 320.354 869.475) 
(list 320.3548 869.4853) 
(list 320.3576 869.4956) 
(list 320.3624 869.5058) 
(list 320.369 869.5161) 
(list 320.3772 869.5264) 
(list 320.3869 869.5367) 
(list 320.3976 869.5469) 
(list 320.4092 869.5572) 
(list 320.4212 869.5675) 
(list 320.4333 869.5778) 
(list 320.4451 869.5881) 
(list 320.4563 869.5983) 
(list 320.4664 869.6086) 
(list 320.4753 869.6189) 
(list 320.4826 869.6292) 
(list 320.488 869.6394) 
(list 320.4915 869.6497) 
(list 320.4929 869.66) 
(list 320.4929 869.66)))
(apply 'command (append '("pline") coords '("c")))
(setq tap1 (ssadd (entlast) tap1))
(command "_mirror" (entlast) "" "320,900" "320,901" "No")
(setq tap1 (ssadd (entlast) tap1))
(setq coords (list 
(list 321.122 869.29) 
(list 320.4929 869.29) 
(list 320.4929 869.3003) 
(list 320.4929 869.3106) 
(list 320.4929 869.3208) 
(list 320.4929 869.3311) 
(list 320.4929 869.3414) 
(list 320.4929 869.3517) 
(list 320.4929 869.3619) 
(list 320.4929 869.3722) 
(list 320.4929 869.3825) 
(list 320.4929 869.3928) 
(list 320.4929 869.4031) 
(list 320.4929 869.4133) 
(list 320.4929 869.4236) 
(list 320.4929 869.4339) 
(list 320.4929 869.4442) 
(list 320.4929 869.4544) 
(list 320.4929 869.4647) 
(list 320.4929 869.475) 
(list 320.4929 869.4853) 
(list 320.4929 869.4956) 
(list 320.4929 869.5058) 
(list 320.4929 869.5161) 
(list 320.4929 869.5264) 
(list 320.4929 869.5367) 
(list 320.4929 869.5469) 
(list 320.4929 869.5572) 
(list 320.4929 869.5675) 
(list 320.4929 869.5778) 
(list 320.4929 869.5881) 
(list 320.4929 869.5983) 
(list 320.4929 869.6086) 
(list 320.4929 869.6189) 
(list 320.4929 869.6292) 
(list 320.4929 869.6394) 
(list 320.4929 869.6497) 
(list 320.4929 869.66) 
(list 321.122 869.66)))
(apply 'command (append '("pline") coords '("c")))
(setq tap1 (ssadd (entlast) tap1))
(command "_mirror" (entlast) "" "320,900" "320,901" "No")
(setq tap1 (ssadd (entlast) tap1))
(setq coords (list 
(list 320 869.66) 
(list 320.135 869.66) 
(list 320.135 869.6703) 
(list 320.135 869.6806) 
(list 320.135 869.6908) 
(list 320.135 869.7011) 
(list 320.135 869.7114) 
(list 320.135 869.7217) 
(list 320.135 869.7319) 
(list 320.135 869.7422) 
(list 320.135 869.7525) 
(list 320.135 869.7628) 
(list 320.135 869.7731) 
(list 320.135 869.7833) 
(list 320.135 869.7936) 
(list 320.135 869.8039) 
(list 320.135 869.8142) 
(list 320.135 869.8244) 
(list 320.135 869.8347) 
(list 320.135 869.845) 
(list 320.135 869.8553) 
(list 320.135 869.8656) 
(list 320.135 869.8758) 
(list 320.135 869.8861) 
(list 320.135 869.8964) 
(list 320.135 869.9067) 
(list 320.135 869.9169) 
(list 320.135 869.9272) 
(list 320.135 869.9375) 
(list 320.135 869.9478) 
(list 320.135 869.9581) 
(list 320.135 869.9683) 
(list 320.135 869.9786) 
(list 320.135 869.9889) 
(list 320.135 869.9992) 
(list 320.135 870.0094) 
(list 320.135 870.0197) 
(list 320.135 870.03) 
(list 320 870.03)))
(apply 'command (append '("pline") coords '("c")))
(setq tap1 (ssadd (entlast) tap1))
(command "_mirror" (entlast) "" "320,900" "320,901" "No")
(setq tap1 (ssadd (entlast) tap1))
(setq coords (list 
(list 320.5026 869.66) 
(list 320.4929 869.66) 
(list 320.492 869.6703) 
(list 320.4891 869.6806) 
(list 320.484 869.6908) 
(list 320.477 869.7011) 
(list 320.4682 869.7114) 
(list 320.458 869.7217) 
(list 320.4466 869.7319) 
(list 320.4343 869.7422) 
(list 320.4216 869.7525) 
(list 320.4088 869.7628) 
(list 320.3963 869.7731) 
(list 320.3844 869.7833) 
(list 320.3737 869.7936) 
(list 320.3643 869.8039) 
(list 320.3566 869.8142) 
(list 320.3509 869.8244) 
(list 320.3472 869.8347) 
(list 320.3459 869.845) 
(list 320.3468 869.8553) 
(list 320.35 869.8656) 
(list 320.3555 869.8758) 
(list 320.363 869.8861) 
(list 320.3723 869.8964) 
(list 320.3832 869.9067) 
(list 320.3954 869.9169) 
(list 320.4084 869.9272) 
(list 320.422 869.9375) 
(list 320.4356 869.9478) 
(list 320.4489 869.9581) 
(list 320.4615 869.9683) 
(list 320.473 869.9786) 
(list 320.4829 869.9889) 
(list 320.4911 869.9992) 
(list 320.4972 870.0094) 
(list 320.5011 870.0197) 
(list 320.5026 870.03) 
(list 320.5026 870.03)))
(apply 'command (append '("pline") coords '("c")))
(setq tap1 (ssadd (entlast) tap1))
(command "_mirror" (entlast) "" "320,900" "320,901" "No")
(setq tap1 (ssadd (entlast) tap1))
(setq coords (list 
(list 321.122 869.66) 
(list 320.5026 869.66) 
(list 320.5026 869.6703) 
(list 320.5026 869.6806) 
(list 320.5026 869.6908) 
(list 320.5026 869.7011) 
(list 320.5026 869.7114) 
(list 320.5026 869.7217) 
(list 320.5026 869.7319) 
(list 320.5026 869.7422) 
(list 320.5026 869.7525) 
(list 320.5026 869.7628) 
(list 320.5026 869.7731) 
(list 320.5026 869.7833) 
(list 320.5026 869.7936) 
(list 320.5026 869.8039) 
(list 320.5026 869.8142) 
(list 320.5026 869.8244) 
(list 320.5026 869.8347) 
(list 320.5026 869.845) 
(list 320.5026 869.8553) 
(list 320.5026 869.8656) 
(list 320.5026 869.8758) 
(list 320.5026 869.8861) 
(list 320.5026 869.8964) 
(list 320.5026 869.9067) 
(list 320.5026 869.9169) 
(list 320.5026 869.9272) 
(list 320.5026 869.9375) 
(list 320.5026 869.9478) 
(list 320.5026 869.9581) 
(list 320.5026 869.9683) 
(list 320.5026 869.9786) 
(list 320.5026 869.9889) 
(list 320.5026 869.9992) 
(list 320.5026 870.0094) 
(list 320.5026 870.0197) 
(list 320.5026 870.03) 
(list 321.122 870.03)))
(apply 'command (append '("pline") coords '("c")))
(setq tap1 (ssadd (entlast) tap1))
(command "_mirror" (entlast) "" "320,900" "320,901" "No")
(setq tap1 (ssadd (entlast) tap1))
(setq coords (list 
(list 320 870.03) 
(list 320.135 870.03) 
(list 320.135 870.0403) 
(list 320.135 870.0506) 
(list 320.135 870.0608) 
(list 320.135 870.0711) 
(list 320.135 870.0814) 
(list 320.135 870.0917) 
(list 320.135 870.1019) 
(list 320.135 870.1122) 
(list 320.135 870.1225) 
(list 320.135 870.1328) 
(list 320.135 870.1431) 
(list 320.135 870.1533) 
(list 320.135 870.1636) 
(list 320.135 870.1739) 
(list 320.135 870.1842) 
(list 320.135 870.1944) 
(list 320.135 870.2047) 
(list 320.135 870.215) 
(list 320.135 870.2253) 
(list 320.135 870.2356) 
(list 320.135 870.2458) 
(list 320.135 870.2561) 
(list 320.135 870.2664) 
(list 320.135 870.2767) 
(list 320.135 870.2869) 
(list 320.135 870.2972) 
(list 320.135 870.3075) 
(list 320.135 870.3178) 
(list 320.135 870.3281) 
(list 320.135 870.3383) 
(list 320.135 870.3486) 
(list 320.135 870.3589) 
(list 320.135 870.3692) 
(list 320.135 870.3794) 
(list 320.135 870.3897) 
(list 320.135 870.4) 
(list 320 870.4)))
(apply 'command (append '("pline") coords '("c")))
(setq tap1 (ssadd (entlast) tap1))
(command "_mirror" (entlast) "" "320,900" "320,901" "No")
(setq tap1 (ssadd (entlast) tap1))
(setq coords (list 
(list 320.5123 870.03) 
(list 320.5026 870.03) 
(list 320.5016 870.0403) 
(list 320.4983 870.0506) 
(list 320.4925 870.0608) 
(list 320.4846 870.0711) 
(list 320.4748 870.0814) 
(list 320.4633 870.0917) 
(list 320.4504 870.1019) 
(list 320.4367 870.1122) 
(list 320.4224 870.1225) 
(list 320.408 870.1328) 
(list 320.394 870.1431) 
(list 320.3808 870.1533) 
(list 320.3687 870.1636) 
(list 320.3583 870.1739) 
(list 320.3497 870.1842) 
(list 320.3433 870.1944) 
(list 320.3392 870.2047) 
(list 320.3377 870.215) 
(list 320.3388 870.2253) 
(list 320.3424 870.2356) 
(list 320.3485 870.2458) 
(list 320.3569 870.2561) 
(list 320.3674 870.2664) 
(list 320.3796 870.2767) 
(list 320.3931 870.2869) 
(list 320.4077 870.2972) 
(list 320.4228 870.3075) 
(list 320.438 870.3178) 
(list 320.4528 870.3281) 
(list 320.4668 870.3383) 
(list 320.4795 870.3486) 
(list 320.4906 870.3589) 
(list 320.4997 870.3692) 
(list 320.5064 870.3794) 
(list 320.5107 870.3897) 
(list 320.5123 870.4) 
(list 320.5123 870.4)))
(apply 'command (append '("pline") coords '("c")))
(setq tap1 (ssadd (entlast) tap1))
(command "_mirror" (entlast) "" "320,900" "320,901" "No")
(setq tap1 (ssadd (entlast) tap1))
(setq coords (list 
(list 321.122 870.03) 
(list 320.5123 870.03) 
(list 320.5123 870.0403) 
(list 320.5123 870.0506) 
(list 320.5123 870.0608) 
(list 320.5123 870.0711) 
(list 320.5123 870.0814) 
(list 320.5123 870.0917) 
(list 320.5123 870.1019) 
(list 320.5123 870.1122) 
(list 320.5123 870.1225) 
(list 320.5123 870.1328) 
(list 320.5123 870.1431) 
(list 320.5123 870.1533) 
(list 320.5123 870.1636) 
(list 320.5123 870.1739) 
(list 320.5123 870.1842) 
(list 320.5123 870.1944) 
(list 320.5123 870.2047) 
(list 320.5123 870.215) 
(list 320.5123 870.2253) 
(list 320.5123 870.2356) 
(list 320.5123 870.2458) 
(list 320.5123 870.2561) 
(list 320.5123 870.2664) 
(list 320.5123 870.2767) 
(list 320.5123 870.2869) 
(list 320.5123 870.2972) 
(list 320.5123 870.3075) 
(list 320.5123 870.3178) 
(list 320.5123 870.3281) 
(list 320.5123 870.3383) 
(list 320.5123 870.3486) 
(list 320.5123 870.3589) 
(list 320.5123 870.3692) 
(list 320.5123 870.3794) 
(list 320.5123 870.3897) 
(list 320.5123 870.4) 
(list 321.122 870.4)))
(apply 'command (append '("pline") coords '("c")))
(setq tap1 (ssadd (entlast) tap1))
(command "_mirror" (entlast) "" "320,900" "320,901" "No")
(setq tap1 (ssadd (entlast) tap1))
(setq coords (list 
(list 320 870.4) 
(list 320.135 870.4) 
(list 320.135 870.4103) 
(list 320.135 870.4206) 
(list 320.135 870.4308) 
(list 320.135 870.4411) 
(list 320.135 870.4514) 
(list 320.135 870.4617) 
(list 320.135 870.4719) 
(list 320.135 870.4822) 
(list 320.135 870.4925) 
(list 320.135 870.5028) 
(list 320.135 870.5131) 
(list 320.135 870.5233) 
(list 320.135 870.5336) 
(list 320.135 870.5439) 
(list 320.135 870.5542) 
(list 320.135 870.5644) 
(list 320.135 870.5747) 
(list 320.135 870.585) 
(list 320.135 870.5953) 
(list 320.135 870.6056) 
(list 320.135 870.6158) 
(list 320.135 870.6261) 
(list 320.135 870.6364) 
(list 320.135 870.6467) 
(list 320.135 870.6569) 
(list 320.135 870.6672) 
(list 320.135 870.6775) 
(list 320.135 870.6878) 
(list 320.135 870.6981) 
(list 320.135 870.7083) 
(list 320.135 870.7186) 
(list 320.135 870.7289) 
(list 320.135 870.7392) 
(list 320.135 870.7494) 
(list 320.135 870.7597) 
(list 320.135 870.77) 
(list 320 870.77)))
(apply 'command (append '("pline") coords '("c")))
(setq tap1 (ssadd (entlast) tap1))
(command "_mirror" (entlast) "" "320,900" "320,901" "No")
(setq tap1 (ssadd (entlast) tap1))
(setq coords (list 
(list 320.5221 870.4) 
(list 320.5123 870.4) 
(list 320.5112 870.4103) 
(list 320.5075 870.4206) 
(list 320.5011 870.4308) 
(list 320.4923 870.4411) 
(list 320.4813 870.4514) 
(list 320.4685 870.4617) 
(list 320.4543 870.4719) 
(list 320.439 870.4822) 
(list 320.4232 870.4925) 
(list 320.4073 870.5028) 
(list 320.3918 870.5131) 
(list 320.3771 870.5233) 
(list 320.3638 870.5336) 
(list 320.3522 870.5439) 
(list 320.3427 870.5542) 
(list 320.3357 870.5644) 
(list 320.3312 870.5747) 
(list 320.3296 870.585) 
(list 320.3308 870.5953) 
(list 320.3348 870.6056) 
(list 320.3416 870.6158) 
(list 320.3509 870.6261) 
(list 320.3624 870.6364) 
(list 320.3759 870.6467) 
(list 320.3909 870.6569) 
(list 320.4069 870.6672) 
(list 320.4236 870.6775) 
(list 320.4403 870.6878) 
(list 320.4567 870.6981) 
(list 320.4721 870.7083) 
(list 320.4861 870.7186) 
(list 320.4982 870.7289) 
(list 320.5082 870.7392) 
(list 320.5156 870.7494) 
(list 320.5203 870.7597) 
(list 320.5221 870.77) 
(list 320.5221 870.77)))
(apply 'command (append '("pline") coords '("c")))
(setq tap1 (ssadd (entlast) tap1))
(command "_mirror" (entlast) "" "320,900" "320,901" "No")
(setq tap1 (ssadd (entlast) tap1))
(setq coords (list 
(list 321.122 870.4) 
(list 320.5221 870.4) 
(list 320.5221 870.4103) 
(list 320.5221 870.4206) 
(list 320.5221 870.4308) 
(list 320.5221 870.4411) 
(list 320.5221 870.4514) 
(list 320.5221 870.4617) 
(list 320.5221 870.4719) 
(list 320.5221 870.4822) 
(list 320.5221 870.4925) 
(list 320.5221 870.5028) 
(list 320.5221 870.5131) 
(list 320.5221 870.5233) 
(list 320.5221 870.5336) 
(list 320.5221 870.5439) 
(list 320.5221 870.5542) 
(list 320.5221 870.5644) 
(list 320.5221 870.5747) 
(list 320.5221 870.585) 
(list 320.5221 870.5953) 
(list 320.5221 870.6056) 
(list 320.5221 870.6158) 
(list 320.5221 870.6261) 
(list 320.5221 870.6364) 
(list 320.5221 870.6467) 
(list 320.5221 870.6569) 
(list 320.5221 870.6672) 
(list 320.5221 870.6775) 
(list 320.5221 870.6878) 
(list 320.5221 870.6981) 
(list 320.5221 870.7083) 
(list 320.5221 870.7186) 
(list 320.5221 870.7289) 
(list 320.5221 870.7392) 
(list 320.5221 870.7494) 
(list 320.5221 870.7597) 
(list 320.5221 870.77) 
(list 321.122 870.77)))
(apply 'command (append '("pline") coords '("c")))
(setq tap1 (ssadd (entlast) tap1))
(command "_mirror" (entlast) "" "320,900" "320,901" "No")
(setq tap1 (ssadd (entlast) tap1))
(setq coords (list 
(list 320 870.77) 
(list 320.135 870.77) 
(list 320.135 870.7803) 
(list 320.135 870.7906) 
(list 320.135 870.8008) 
(list 320.135 870.8111) 
(list 320.135 870.8214) 
(list 320.135 870.8317) 
(list 320.135 870.8419) 
(list 320.135 870.8522) 
(list 320.135 870.8625) 
(list 320.135 870.8728) 
(list 320.135 870.8831) 
(list 320.135 870.8933) 
(list 320.135 870.9036) 
(list 320.135 870.9139) 
(list 320.135 870.9242) 
(list 320.135 870.9344) 
(list 320.135 870.9447) 
(list 320.135 870.955) 
(list 320.135 870.9653) 
(list 320.135 870.9756) 
(list 320.135 870.9858) 
(list 320.135 870.9961) 
(list 320.135 871.0064) 
(list 320.135 871.0167) 
(list 320.135 871.0269) 
(list 320.135 871.0372) 
(list 320.135 871.0475) 
(list 320.135 871.0578) 
(list 320.135 871.0681) 
(list 320.135 871.0783) 
(list 320.135 871.0886) 
(list 320.135 871.0989) 
(list 320.135 871.1092) 
(list 320.135 871.1194) 
(list 320.135 871.1297) 
(list 320.135 871.14) 
(list 320 871.14)))
(apply 'command (append '("pline") coords '("c")))
(setq tap1 (ssadd (entlast) tap1))
(command "_mirror" (entlast) "" "320,900" "320,901" "No")
(setq tap1 (ssadd (entlast) tap1))
(setq coords (list 
(list 320.5318 870.77) 
(list 320.5221 870.77) 
(list 320.5208 870.7803) 
(list 320.5167 870.7906) 
(list 320.5096 870.8008) 
(list 320.4999 870.8111) 
(list 320.4879 870.8214) 
(list 320.4738 870.8317) 
(list 320.4582 870.8419) 
(list 320.4414 870.8522) 
(list 320.424 870.8625) 
(list 320.4065 870.8728) 
(list 320.3895 870.8831) 
(list 320.3734 870.8933) 
(list 320.3589 870.9036) 
(list 320.3462 870.9139) 
(list 320.3358 870.9242) 
(list 320.3281 870.9344) 
(list 320.3232 870.9447) 
(list 320.3215 870.955) 
(list 320.3228 870.9653) 
(list 320.3272 870.9756) 
(list 320.3347 870.9858) 
(list 320.3448 870.9961) 
(list 320.3575 871.0064) 
(list 320.3722 871.0167) 
(list 320.3886 871.0269) 
(list 320.4062 871.0372) 
(list 320.4244 871.0475) 
(list 320.4427 871.0578) 
(list 320.4605 871.0681) 
(list 320.4773 871.0783) 
(list 320.4926 871.0886) 
(list 320.5059 871.0989) 
(list 320.5167 871.1092) 
(list 320.5248 871.1194) 
(list 320.5299 871.1297) 
(list 320.5318 871.14) 
(list 320.5318 871.14)))
(apply 'command (append '("pline") coords '("c")))
(setq tap1 (ssadd (entlast) tap1))
(command "_mirror" (entlast) "" "320,900" "320,901" "No")
(setq tap1 (ssadd (entlast) tap1))
(setq coords (list 
(list 321.122 870.77) 
(list 320.5318 870.77) 
(list 320.5318 870.7803) 
(list 320.5318 870.7906) 
(list 320.5318 870.8008) 
(list 320.5318 870.8111) 
(list 320.5318 870.8214) 
(list 320.5318 870.8317) 
(list 320.5318 870.8419) 
(list 320.5318 870.8522) 
(list 320.5318 870.8625) 
(list 320.5318 870.8728) 
(list 320.5318 870.8831) 
(list 320.5318 870.8933) 
(list 320.5318 870.9036) 
(list 320.5318 870.9139) 
(list 320.5318 870.9242) 
(list 320.5318 870.9344) 
(list 320.5318 870.9447) 
(list 320.5318 870.955) 
(list 320.5318 870.9653) 
(list 320.5318 870.9756) 
(list 320.5318 870.9858) 
(list 320.5318 870.9961) 
(list 320.5318 871.0064) 
(list 320.5318 871.0167) 
(list 320.5318 871.0269) 
(list 320.5318 871.0372) 
(list 320.5318 871.0475) 
(list 320.5318 871.0578) 
(list 320.5318 871.0681) 
(list 320.5318 871.0783) 
(list 320.5318 871.0886) 
(list 320.5318 871.0989) 
(list 320.5318 871.1092) 
(list 320.5318 871.1194) 
(list 320.5318 871.1297) 
(list 320.5318 871.14) 
(list 321.122 871.14)))
(apply 'command (append '("pline") coords '("c")))
(setq tap1 (ssadd (entlast) tap1))
(command "_mirror" (entlast) "" "320,900" "320,901" "No")
(setq tap1 (ssadd (entlast) tap1))
(setq coords (list 
(list 320 871.14) 
(list 320.135 871.14) 
(list 320.135 871.1503) 
(list 320.135 871.1606) 
(list 320.135 871.1708) 
(list 320.135 871.1811) 
(list 320.135 871.1914) 
(list 320.135 871.2017) 
(list 320.135 871.2119) 
(list 320.135 871.2222) 
(list 320.135 871.2325) 
(list 320.135 871.2428) 
(list 320.135 871.2531) 
(list 320.135 871.2633) 
(list 320.135 871.2736) 
(list 320.135 871.2839) 
(list 320.135 871.2942) 
(list 320.135 871.3044) 
(list 320.135 871.3147) 
(list 320.135 871.325) 
(list 320.135 871.3353) 
(list 320.135 871.3456) 
(list 320.135 871.3558) 
(list 320.135 871.3661) 
(list 320.135 871.3764) 
(list 320.135 871.3867) 
(list 320.135 871.3969) 
(list 320.135 871.4072) 
(list 320.135 871.4175) 
(list 320.135 871.4278) 
(list 320.135 871.4381) 
(list 320.135 871.4483) 
(list 320.135 871.4586) 
(list 320.135 871.4689) 
(list 320.135 871.4792) 
(list 320.135 871.4894) 
(list 320.135 871.4997) 
(list 320.135 871.51) 
(list 320 871.51)))
(apply 'command (append '("pline") coords '("c")))
(setq tap1 (ssadd (entlast) tap1))
(command "_mirror" (entlast) "" "320,900" "320,901" "No")
(setq tap1 (ssadd (entlast) tap1))
(setq coords (list 
(list 320.5415 871.14) 
(list 320.5318 871.14) 
(list 320.5304 871.1503) 
(list 320.5258 871.1606) 
(list 320.5181 871.1708) 
(list 320.5076 871.1811) 
(list 320.4944 871.1914) 
(list 320.4791 871.2017) 
(list 320.462 871.2119) 
(list 320.4437 871.2222) 
(list 320.4248 871.2325) 
(list 320.4058 871.2428) 
(list 320.3872 871.2531) 
(list 320.3698 871.2633) 
(list 320.3539 871.2736) 
(list 320.3401 871.2839) 
(list 320.3289 871.2942) 
(list 320.3205 871.3044) 
(list 320.3153 871.3147) 
(list 320.3133 871.325) 
(list 320.3148 871.3353) 
(list 320.3196 871.3456) 
(list 320.3277 871.3558) 
(list 320.3388 871.3661) 
(list 320.3525 871.3764) 
(list 320.3686 871.3867) 
(list 320.3864 871.3969) 
(list 320.4054 871.4072) 
(list 320.4252 871.4175) 
(list 320.445 871.4278) 
(list 320.4644 871.4381) 
(list 320.4826 871.4483) 
(list 320.4991 871.4586) 
(list 320.5135 871.4689) 
(list 320.5253 871.4792) 
(list 320.534 871.4894) 
(list 320.5395 871.4997) 
(list 320.5415 871.51) 
(list 320.5415 871.51)))
(apply 'command (append '("pline") coords '("c")))
(setq tap1 (ssadd (entlast) tap1))
(command "_mirror" (entlast) "" "320,900" "320,901" "No")
(setq tap1 (ssadd (entlast) tap1))
(setq coords (list 
(list 321.122 871.14) 
(list 320.5415 871.14) 
(list 320.5415 871.1503) 
(list 320.5415 871.1606) 
(list 320.5415 871.1708) 
(list 320.5415 871.1811) 
(list 320.5415 871.1914) 
(list 320.5415 871.2017) 
(list 320.5415 871.2119) 
(list 320.5415 871.2222) 
(list 320.5415 871.2325) 
(list 320.5415 871.2428) 
(list 320.5415 871.2531) 
(list 320.5415 871.2633) 
(list 320.5415 871.2736) 
(list 320.5415 871.2839) 
(list 320.5415 871.2942) 
(list 320.5415 871.3044) 
(list 320.5415 871.3147) 
(list 320.5415 871.325) 
(list 320.5415 871.3353) 
(list 320.5415 871.3456) 
(list 320.5415 871.3558) 
(list 320.5415 871.3661) 
(list 320.5415 871.3764) 
(list 320.5415 871.3867) 
(list 320.5415 871.3969) 
(list 320.5415 871.4072) 
(list 320.5415 871.4175) 
(list 320.5415 871.4278) 
(list 320.5415 871.4381) 
(list 320.5415 871.4483) 
(list 320.5415 871.4586) 
(list 320.5415 871.4689) 
(list 320.5415 871.4792) 
(list 320.5415 871.4894) 
(list 320.5415 871.4997) 
(list 320.5415 871.51) 
(list 321.122 871.51)))
(apply 'command (append '("pline") coords '("c")))
(setq tap1 (ssadd (entlast) tap1))
(command "_mirror" (entlast) "" "320,900" "320,901" "No")
(setq tap1 (ssadd (entlast) tap1))
(setq coords (list 
(list 320 871.51) 
(list 320.135 871.51) 
(list 320.135 871.5203) 
(list 320.135 871.5306) 
(list 320.135 871.5408) 
(list 320.135 871.5511) 
(list 320.135 871.5614) 
(list 320.135 871.5717) 
(list 320.135 871.5819) 
(list 320.135 871.5922) 
(list 320.135 871.6025) 
(list 320.135 871.6128) 
(list 320.135 871.6231) 
(list 320.135 871.6333) 
(list 320.135 871.6436) 
(list 320.135 871.6539) 
(list 320.135 871.6642) 
(list 320.135 871.6744) 
(list 320.135 871.6847) 
(list 320.135 871.695) 
(list 320.135 871.7053) 
(list 320.135 871.7156) 
(list 320.135 871.7258) 
(list 320.135 871.7361) 
(list 320.135 871.7464) 
(list 320.135 871.7567) 
(list 320.135 871.7669) 
(list 320.135 871.7772) 
(list 320.135 871.7875) 
(list 320.135 871.7978) 
(list 320.135 871.8081) 
(list 320.135 871.8183) 
(list 320.135 871.8286) 
(list 320.135 871.8389) 
(list 320.135 871.8492) 
(list 320.135 871.8594) 
(list 320.135 871.8697) 
(list 320.135 871.88) 
(list 320 871.88)))
(apply 'command (append '("pline") coords '("c")))
(setq tap1 (ssadd (entlast) tap1))
(command "_mirror" (entlast) "" "320,900" "320,901" "No")
(setq tap1 (ssadd (entlast) tap1))
(setq coords (list 
(list 320.5513 871.51) 
(list 320.5415 871.51) 
(list 320.54 871.5203) 
(list 320.535 871.5306) 
(list 320.5267 871.5408) 
(list 320.5152 871.5511) 
(list 320.501 871.5614) 
(list 320.4843 871.5717) 
(list 320.4659 871.5819) 
(list 320.4461 871.5922) 
(list 320.4256 871.6025) 
(list 320.405 871.6128) 
(list 320.385 871.6231) 
(list 320.3661 871.6333) 
(list 320.349 871.6436) 
(list 320.3341 871.6539) 
(list 320.3219 871.6642) 
(list 320.3129 871.6744) 
(list 320.3073 871.6847) 
(list 320.3052 871.695) 
(list 320.3068 871.7053) 
(list 320.3121 871.7156) 
(list 320.3208 871.7258) 
(list 320.3327 871.7361) 
(list 320.3476 871.7464) 
(list 320.3649 871.7567) 
(list 320.3841 871.7669) 
(list 320.4047 871.7772) 
(list 320.426 871.7875) 
(list 320.4474 871.7978) 
(list 320.4682 871.8081) 
(list 320.4879 871.8183) 
(list 320.5057 871.8286) 
(list 320.5212 871.8389) 
(list 320.5338 871.8492) 
(list 320.5432 871.8594) 
(list 320.5491 871.8697) 
(list 320.5513 871.88) 
(list 320.5513 871.88)))
(apply 'command (append '("pline") coords '("c")))
(setq tap1 (ssadd (entlast) tap1))
(command "_mirror" (entlast) "" "320,900" "320,901" "No")
(setq tap1 (ssadd (entlast) tap1))
(setq coords (list 
(list 321.122 871.51) 
(list 320.5513 871.51) 
(list 320.5513 871.5203) 
(list 320.5513 871.5306) 
(list 320.5513 871.5408) 
(list 320.5513 871.5511) 
(list 320.5513 871.5614) 
(list 320.5513 871.5717) 
(list 320.5513 871.5819) 
(list 320.5513 871.5922) 
(list 320.5513 871.6025) 
(list 320.5513 871.6128) 
(list 320.5513 871.6231) 
(list 320.5513 871.6333) 
(list 320.5513 871.6436) 
(list 320.5513 871.6539) 
(list 320.5513 871.6642) 
(list 320.5513 871.6744) 
(list 320.5513 871.6847) 
(list 320.5513 871.695) 
(list 320.5513 871.7053) 
(list 320.5513 871.7156) 
(list 320.5513 871.7258) 
(list 320.5513 871.7361) 
(list 320.5513 871.7464) 
(list 320.5513 871.7567) 
(list 320.5513 871.7669) 
(list 320.5513 871.7772) 
(list 320.5513 871.7875) 
(list 320.5513 871.7978) 
(list 320.5513 871.8081) 
(list 320.5513 871.8183) 
(list 320.5513 871.8286) 
(list 320.5513 871.8389) 
(list 320.5513 871.8492) 
(list 320.5513 871.8594) 
(list 320.5513 871.8697) 
(list 320.5513 871.88) 
(list 321.122 871.88)))
(apply 'command (append '("pline") coords '("c")))
(setq tap1 (ssadd (entlast) tap1))
(command "_mirror" (entlast) "" "320,900" "320,901" "No")
(setq tap1 (ssadd (entlast) tap1))
(setq coords (list 
(list 320 871.88) 
(list 320.135 871.88) 
(list 320.135 871.8903) 
(list 320.135 871.9006) 
(list 320.135 871.9108) 
(list 320.135 871.9211) 
(list 320.135 871.9314) 
(list 320.135 871.9417) 
(list 320.135 871.9519) 
(list 320.135 871.9622) 
(list 320.135 871.9725) 
(list 320.135 871.9828) 
(list 320.135 871.9931) 
(list 320.135 872.0033) 
(list 320.135 872.0136) 
(list 320.135 872.0239) 
(list 320.135 872.0342) 
(list 320.135 872.0444) 
(list 320.135 872.0547) 
(list 320.135 872.065) 
(list 320.135 872.0753) 
(list 320.135 872.0856) 
(list 320.135 872.0958) 
(list 320.135 872.1061) 
(list 320.135 872.1164) 
(list 320.135 872.1267) 
(list 320.135 872.1369) 
(list 320.135 872.1472) 
(list 320.135 872.1575) 
(list 320.135 872.1678) 
(list 320.135 872.1781) 
(list 320.135 872.1883) 
(list 320.135 872.1986) 
(list 320.135 872.2089) 
(list 320.135 872.2192) 
(list 320.135 872.2294) 
(list 320.135 872.2397) 
(list 320.135 872.25) 
(list 320 872.25)))
(apply 'command (append '("pline") coords '("c")))
(setq tap1 (ssadd (entlast) tap1))
(command "_mirror" (entlast) "" "320,900" "320,901" "No")
(setq tap1 (ssadd (entlast) tap1))
(setq coords (list 
(list 320.561 871.88) 
(list 320.5513 871.88) 
(list 320.5496 871.8903) 
(list 320.5442 871.9006) 
(list 320.5352 871.9108) 
(list 320.5229 871.9211) 
(list 320.5075 871.9314) 
(list 320.4896 871.9417) 
(list 320.4697 871.9519) 
(list 320.4484 871.9622) 
(list 320.4264 871.9725) 
(list 320.4043 871.9828) 
(list 320.3827 871.9931) 
(list 320.3624 872.0033) 
(list 320.344 872.0136) 
(list 320.328 872.0239) 
(list 320.315 872.0342) 
(list 320.3053 872.0444) 
(list 320.2993 872.0547) 
(list 320.2971 872.065) 
(list 320.2988 872.0753) 
(list 320.3045 872.0856) 
(list 320.3138 872.0958) 
(list 320.3267 872.1061) 
(list 320.3427 872.1164) 
(list 320.3612 872.1267) 
(list 320.3819 872.1369) 
(list 320.4039 872.1472) 
(list 320.4268 872.1575) 
(list 320.4497 872.1678) 
(list 320.4721 872.1781) 
(list 320.4931 872.1883) 
(list 320.5122 872.1986) 
(list 320.5288 872.2089) 
(list 320.5423 872.2192) 
(list 320.5524 872.2294) 
(list 320.5587 872.2397) 
(list 320.561 872.25) 
(list 320.561 872.25)))
(apply 'command (append '("pline") coords '("c")))
(setq tap1 (ssadd (entlast) tap1))
(command "_mirror" (entlast) "" "320,900" "320,901" "No")
(setq tap1 (ssadd (entlast) tap1))
(setq coords (list 
(list 321.122 871.88) 
(list 320.561 871.88) 
(list 320.561 871.8903) 
(list 320.561 871.9006) 
(list 320.561 871.9108) 
(list 320.561 871.9211) 
(list 320.561 871.9314) 
(list 320.561 871.9417) 
(list 320.561 871.9519) 
(list 320.561 871.9622) 
(list 320.561 871.9725) 
(list 320.561 871.9828) 
(list 320.561 871.9931) 
(list 320.561 872.0033) 
(list 320.561 872.0136) 
(list 320.561 872.0239) 
(list 320.561 872.0342) 
(list 320.561 872.0444) 
(list 320.561 872.0547) 
(list 320.561 872.065) 
(list 320.561 872.0753) 
(list 320.561 872.0856) 
(list 320.561 872.0958) 
(list 320.561 872.1061) 
(list 320.561 872.1164) 
(list 320.561 872.1267) 
(list 320.561 872.1369) 
(list 320.561 872.1472) 
(list 320.561 872.1575) 
(list 320.561 872.1678) 
(list 320.561 872.1781) 
(list 320.561 872.1883) 
(list 320.561 872.1986) 
(list 320.561 872.2089) 
(list 320.561 872.2192) 
(list 320.561 872.2294) 
(list 320.561 872.2397) 
(list 320.561 872.25) 
(list 321.122 872.25)))
(apply 'command (append '("pline") coords '("c")))
(setq tap1 (ssadd (entlast) tap1))
(command "_mirror" (entlast) "" "320,900" "320,901" "No")
(setq tap1 (ssadd (entlast) tap1))
(command "_block" "blktap1" "320,900" tap1 "")
(command "_insert" "blktap1" "320,900" "1" "1" "0")
(command "_insert" "blktap1" "320,900" "1" "1" "180")
(setq uc1 nil)
(setq uc1 (ssadd))
(setq coords (list 
(list 0 -0.185) 
(list 0.135 -0.185) 
(list 0.135 -0.17472) 
(list 0.135 -0.16444) 
(list 0.135 -0.15417) 
(list 0.135 -0.14389) 
(list 0.135 -0.13361) 
(list 0.135 -0.12333) 
(list 0.135 -0.11306) 
(list 0.135 -0.10278) 
(list 0.135 -0.0925) 
(list 0.135 -0.082222) 
(list 0.135 -0.071944) 
(list 0.135 -0.061667) 
(list 0.135 -0.051389) 
(list 0.135 -0.041111) 
(list 0.135 -0.030833) 
(list 0.135 -0.020556) 
(list 0.135 -0.010278) 
(list 0.135 0) 
(list 0.135 0.010278) 
(list 0.135 0.020556) 
(list 0.135 0.030833) 
(list 0.135 0.041111) 
(list 0.135 0.051389) 
(list 0.135 0.061667) 
(list 0.135 0.071944) 
(list 0.135 0.082222) 
(list 0.135 0.0925) 
(list 0.135 0.10278) 
(list 0.135 0.11306) 
(list 0.135 0.12333) 
(list 0.135 0.13361) 
(list 0.135 0.14389) 
(list 0.135 0.15417) 
(list 0.135 0.16444) 
(list 0.135 0.17472) 
(list 0.135 0.185) 
(list 0 0.185)))
(apply 'command (append '("pline") coords '("c")))
(setq uc1 (ssadd (entlast) uc1))
(setq coords (list 
(list 1.122 -0.185) 
(list 0.561 -0.185) 
(list 0.55896 -0.17472) 
(list 0.55292 -0.16444) 
(list 0.54305 -0.15417) 
(list 0.52965 -0.14389) 
(list 0.51313 -0.13361) 
(list 0.494 -0.12333) 
(list 0.47283 -0.11306) 
(list 0.45027 -0.10278) 
(list 0.427 -0.0925) 
(list 0.40373 -0.082222) 
(list 0.38117 -0.071944) 
(list 0.36 -0.061667) 
(list 0.34087 -0.051389) 
(list 0.32435 -0.041111) 
(list 0.31095 -0.030833) 
(list 0.30108 -0.020556) 
(list 0.29504 -0.010278) 
(list 0.293 0) 
(list 0.29504 0.010278) 
(list 0.30108 0.020556) 
(list 0.31095 0.030833) 
(list 0.32435 0.041111) 
(list 0.34087 0.051389) 
(list 0.36 0.061667) 
(list 0.38117 0.071944) 
(list 0.40373 0.082222) 
(list 0.427 0.0925) 
(list 0.45027 0.10278) 
(list 0.47283 0.11306) 
(list 0.494 0.12333) 
(list 0.51313 0.13361) 
(list 0.52965 0.14389) 
(list 0.54305 0.15417) 
(list 0.55292 0.16444) 
(list 0.55896 0.17472) 
(list 0.561 0.185) 
(list 1.122 0.185)))
(apply 'command (append '("pline") coords '("c")))
(setq uc1 (ssadd (entlast) uc1))
(command "_block" "blkuc1" "0,0.185" uc1 "")
(command "_insert" "blkuc1" "320,872.62" "1" "1" "0")
(command "_insert" "blkuc1" "320,872.25" "1" "1" "180")
(command "_insert" "blkuc1" "320,872.99" "1" "1" "0")
(command "_insert" "blkuc1" "320,872.62" "1" "1" "180")
(command "_insert" "blkuc1" "320,873.36" "1" "1" "0")
(command "_insert" "blkuc1" "320,872.99" "1" "1" "180")
(command "_insert" "blkuc1" "320,873.73" "1" "1" "0")
(command "_insert" "blkuc1" "320,873.36" "1" "1" "180")
(command "_insert" "blkuc1" "320,874.1" "1" "1" "0")
(command "_insert" "blkuc1" "320,873.73" "1" "1" "180")
(command "_insert" "blkuc1" "320,874.47" "1" "1" "0")
(command "_insert" "blkuc1" "320,874.1" "1" "1" "180")
(command "_insert" "blkuc1" "320,874.84" "1" "1" "0")
(command "_insert" "blkuc1" "320,874.47" "1" "1" "180")
(command "_insert" "blkuc1" "320,875.21" "1" "1" "0")
(command "_insert" "blkuc1" "320,874.84" "1" "1" "180")
(command "_insert" "blkuc1" "320,875.58" "1" "1" "0")
(command "_insert" "blkuc1" "320,875.21" "1" "1" "180")
(command "_insert" "blkuc1" "320,875.95" "1" "1" "0")
(command "_insert" "blkuc1" "320,875.58" "1" "1" "180")
(command "_insert" "blkuc1" "320,876.32" "1" "1" "0")
(command "_insert" "blkuc1" "320,875.95" "1" "1" "180")
(command "_insert" "blkuc1" "320,876.69" "1" "1" "0")
(command "_insert" "blkuc1" "320,876.32" "1" "1" "180")
(command "_insert" "blkuc1" "320,877.06" "1" "1" "0")
(command "_insert" "blkuc1" "320,876.69" "1" "1" "180")
(command "_insert" "blkuc1" "320,877.43" "1" "1" "0")
(command "_insert" "blkuc1" "320,877.06" "1" "1" "180")
(command "_insert" "blkuc1" "320,877.8" "1" "1" "0")
(command "_insert" "blkuc1" "320,877.43" "1" "1" "180")
(command "_insert" "blkuc1" "320,878.17" "1" "1" "0")
(command "_insert" "blkuc1" "320,877.8" "1" "1" "180")
(command "_insert" "blkuc1" "320,878.54" "1" "1" "0")
(command "_insert" "blkuc1" "320,878.17" "1" "1" "180")
(command "_insert" "blkuc1" "320,878.91" "1" "1" "0")
(command "_insert" "blkuc1" "320,878.54" "1" "1" "180")
(command "_insert" "blkuc1" "320,879.28" "1" "1" "0")
(command "_insert" "blkuc1" "320,878.91" "1" "1" "180")
(command "_insert" "blkuc1" "320,879.65" "1" "1" "0")
(command "_insert" "blkuc1" "320,879.28" "1" "1" "180")
(command "_insert" "blkuc1" "320,880.02" "1" "1" "0")
(command "_insert" "blkuc1" "320,879.65" "1" "1" "180")
(command "_insert" "blkuc1" "320,880.39" "1" "1" "0")
(command "_insert" "blkuc1" "320,880.02" "1" "1" "180")
(command "_insert" "blkuc1" "320,880.76" "1" "1" "0")
(command "_insert" "blkuc1" "320,880.39" "1" "1" "180")
(command "_insert" "blkuc1" "320,881.13" "1" "1" "0")
(command "_insert" "blkuc1" "320,880.76" "1" "1" "180")
(command "_insert" "blkuc1" "320,881.5" "1" "1" "0")
(command "_insert" "blkuc1" "320,881.13" "1" "1" "180")
(command "_insert" "blkuc1" "320,881.87" "1" "1" "0")
(command "_insert" "blkuc1" "320,881.5" "1" "1" "180")
(command "_insert" "blkuc1" "320,882.24" "1" "1" "0")
(command "_insert" "blkuc1" "320,881.87" "1" "1" "180")
(command "_insert" "blkuc1" "320,882.61" "1" "1" "0")
(command "_insert" "blkuc1" "320,882.24" "1" "1" "180")
(command "_insert" "blkuc1" "320,882.98" "1" "1" "0")
(command "_insert" "blkuc1" "320,882.61" "1" "1" "180")
(command "_insert" "blkuc1" "320,883.35" "1" "1" "0")
(command "_insert" "blkuc1" "320,882.98" "1" "1" "180")
(command "_insert" "blkuc1" "320,883.72" "1" "1" "0")
(command "_insert" "blkuc1" "320,883.35" "1" "1" "180")
(command "_insert" "blkuc1" "320,884.09" "1" "1" "0")
(command "_insert" "blkuc1" "320,883.72" "1" "1" "180")
(command "_insert" "blkuc1" "320,884.46" "1" "1" "0")
(command "_insert" "blkuc1" "320,884.09" "1" "1" "180")
(command "_insert" "blkuc1" "320,884.83" "1" "1" "0")
(command "_insert" "blkuc1" "320,884.46" "1" "1" "180")
(command "_insert" "blkuc1" "320,885.2" "1" "1" "0")
(command "_insert" "blkuc1" "320,884.83" "1" "1" "180")
(command "_insert" "blkuc1" "320,885.57" "1" "1" "0")
(command "_insert" "blkuc1" "320,885.2" "1" "1" "180")
(command "_insert" "blkuc1" "320,885.94" "1" "1" "0")
(command "_insert" "blkuc1" "320,885.57" "1" "1" "180")
(command "_insert" "blkuc1" "320,886.31" "1" "1" "0")
(command "_insert" "blkuc1" "320,885.94" "1" "1" "180")
(command "_insert" "blkuc1" "320,886.68" "1" "1" "0")
(command "_insert" "blkuc1" "320,886.31" "1" "1" "180")
(command "_insert" "blkuc1" "320,887.05" "1" "1" "0")
(command "_insert" "blkuc1" "320,886.68" "1" "1" "180")
(command "_insert" "blkuc1" "320,887.42" "1" "1" "0")
(command "_insert" "blkuc1" "320,887.05" "1" "1" "180")
(command "_insert" "blkuc1" "320,887.79" "1" "1" "0")
(command "_insert" "blkuc1" "320,887.42" "1" "1" "180")
(command "_insert" "blkuc1" "320,888.16" "1" "1" "0")
(command "_insert" "blkuc1" "320,887.79" "1" "1" "180")
(command "_insert" "blkuc1" "320,888.53" "1" "1" "0")
(command "_insert" "blkuc1" "320,888.16" "1" "1" "180")
(command "_insert" "blkuc1" "320,888.9" "1" "1" "0")
(command "_insert" "blkuc1" "320,888.53" "1" "1" "180")
(command "_insert" "blkuc1" "320,889.27" "1" "1" "0")
(command "_insert" "blkuc1" "320,888.9" "1" "1" "180")
(command "_insert" "blkuc1" "320,889.64" "1" "1" "0")
(command "_insert" "blkuc1" "320,889.27" "1" "1" "180")
(command "_insert" "blkuc1" "320,890.01" "1" "1" "0")
(command "_insert" "blkuc1" "320,889.64" "1" "1" "180")
(command "_insert" "blkuc1" "320,890.38" "1" "1" "0")
(command "_insert" "blkuc1" "320,890.01" "1" "1" "180")
(command "_insert" "blkuc1" "320,890.75" "1" "1" "0")
(command "_insert" "blkuc1" "320,890.38" "1" "1" "180")
(command "_insert" "blkuc1" "320,891.12" "1" "1" "0")
(command "_insert" "blkuc1" "320,890.75" "1" "1" "180")
(command "_insert" "blkuc1" "320,891.49" "1" "1" "0")
(command "_insert" "blkuc1" "320,891.12" "1" "1" "180")
(command "_insert" "blkuc1" "320,891.86" "1" "1" "0")
(command "_insert" "blkuc1" "320,891.49" "1" "1" "180")
(command "_insert" "blkuc1" "320,892.23" "1" "1" "0")
(command "_insert" "blkuc1" "320,891.86" "1" "1" "180")
(command "_insert" "blkuc1" "320,892.6" "1" "1" "0")
(command "_insert" "blkuc1" "320,892.23" "1" "1" "180")
(command "_insert" "blkuc1" "320,892.97" "1" "1" "0")
(command "_insert" "blkuc1" "320,892.6" "1" "1" "180")
(command "_insert" "blkuc1" "320,893.34" "1" "1" "0")
(command "_insert" "blkuc1" "320,892.97" "1" "1" "180")
(command "_insert" "blkuc1" "320,893.71" "1" "1" "0")
(command "_insert" "blkuc1" "320,893.34" "1" "1" "180")
(command "_insert" "blkuc1" "320,894.08" "1" "1" "0")
(command "_insert" "blkuc1" "320,893.71" "1" "1" "180")
(command "_insert" "blkuc1" "320,894.45" "1" "1" "0")
(command "_insert" "blkuc1" "320,894.08" "1" "1" "180")
(command "_insert" "blkuc1" "320,894.82" "1" "1" "0")
(command "_insert" "blkuc1" "320,894.45" "1" "1" "180")
(command "_insert" "blkuc1" "320,895.19" "1" "1" "0")
(command "_insert" "blkuc1" "320,894.82" "1" "1" "180")
(command "_insert" "blkuc1" "320,895.56" "1" "1" "0")
(command "_insert" "blkuc1" "320,895.19" "1" "1" "180")
(command "_insert" "blkuc1" "320,895.93" "1" "1" "0")
(command "_insert" "blkuc1" "320,895.56" "1" "1" "180")
(command "_insert" "blkuc1" "320,896.3" "1" "1" "0")
(command "_insert" "blkuc1" "320,895.93" "1" "1" "180")
(command "_insert" "blkuc1" "320,896.67" "1" "1" "0")
(command "_insert" "blkuc1" "320,896.3" "1" "1" "180")
(command "_insert" "blkuc1" "320,897.04" "1" "1" "0")
(command "_insert" "blkuc1" "320,896.67" "1" "1" "180")
(command "_insert" "blkuc1" "320,897.41" "1" "1" "0")
(command "_insert" "blkuc1" "320,897.04" "1" "1" "180")
(command "_insert" "blkuc1" "320,897.78" "1" "1" "0")
(command "_insert" "blkuc1" "320,897.41" "1" "1" "180")
(command "_insert" "blkuc1" "320,898.15" "1" "1" "0")
(command "_insert" "blkuc1" "320,897.78" "1" "1" "180")
(command "_insert" "blkuc1" "320,898.52" "1" "1" "0")
(command "_insert" "blkuc1" "320,898.15" "1" "1" "180")
(command "_insert" "blkuc1" "320,898.89" "1" "1" "0")
(command "_insert" "blkuc1" "320,898.52" "1" "1" "180")
(command "_insert" "blkuc1" "320,899.26" "1" "1" "0")
(command "_insert" "blkuc1" "320,898.89" "1" "1" "180")
(command "_insert" "blkuc1" "320,899.63" "1" "1" "0")
(command "_insert" "blkuc1" "320,899.26" "1" "1" "180")
(command "_insert" "blkuc1" "320,900" "1" "1" "0")
(command "_insert" "blkuc1" "320,899.63" "1" "1" "180")
(command "_insert" "blkuc1" "320,900.37" "1" "1" "0")
(command "_insert" "blkuc1" "320,900" "1" "1" "180")
(command "_insert" "blkuc1" "320,900.74" "1" "1" "0")
(command "_insert" "blkuc1" "320,900.37" "1" "1" "180")
(command "_insert" "blkuc1" "320,901.11" "1" "1" "0")
(command "_insert" "blkuc1" "320,900.74" "1" "1" "180")
(command "_insert" "blkuc1" "320,901.48" "1" "1" "0")
(command "_insert" "blkuc1" "320,901.11" "1" "1" "180")
(command "_insert" "blkuc1" "320,901.85" "1" "1" "0")
(command "_insert" "blkuc1" "320,901.48" "1" "1" "180")
(command "_insert" "blkuc1" "320,902.22" "1" "1" "0")
(command "_insert" "blkuc1" "320,901.85" "1" "1" "180")
(command "_insert" "blkuc1" "320,902.59" "1" "1" "0")
(command "_insert" "blkuc1" "320,902.22" "1" "1" "180")
(command "_insert" "blkuc1" "320,902.96" "1" "1" "0")
(command "_insert" "blkuc1" "320,902.59" "1" "1" "180")
(command "_insert" "blkuc1" "320,903.33" "1" "1" "0")
(command "_insert" "blkuc1" "320,902.96" "1" "1" "180")
(command "_insert" "blkuc1" "320,903.7" "1" "1" "0")
(command "_insert" "blkuc1" "320,903.33" "1" "1" "180")
(command "_insert" "blkuc1" "320,904.07" "1" "1" "0")
(command "_insert" "blkuc1" "320,903.7" "1" "1" "180")
(command "_insert" "blkuc1" "320,904.44" "1" "1" "0")
(command "_insert" "blkuc1" "320,904.07" "1" "1" "180")
(command "_insert" "blkuc1" "320,904.81" "1" "1" "0")
(command "_insert" "blkuc1" "320,904.44" "1" "1" "180")
(command "_insert" "blkuc1" "320,905.18" "1" "1" "0")
(command "_insert" "blkuc1" "320,904.81" "1" "1" "180")
(command "_insert" "blkuc1" "320,905.55" "1" "1" "0")
(command "_insert" "blkuc1" "320,905.18" "1" "1" "180")
(command "_insert" "blkuc1" "320,905.92" "1" "1" "0")
(command "_insert" "blkuc1" "320,905.55" "1" "1" "180")
(command "_insert" "blkuc1" "320,906.29" "1" "1" "0")
(command "_insert" "blkuc1" "320,905.92" "1" "1" "180")
(command "_insert" "blkuc1" "320,906.66" "1" "1" "0")
(command "_insert" "blkuc1" "320,906.29" "1" "1" "180")
(command "_insert" "blkuc1" "320,907.03" "1" "1" "0")
(command "_insert" "blkuc1" "320,906.66" "1" "1" "180")
(command "_insert" "blkuc1" "320,907.4" "1" "1" "0")
(command "_insert" "blkuc1" "320,907.03" "1" "1" "180")
(command "_insert" "blkuc1" "320,907.77" "1" "1" "0")
(command "_insert" "blkuc1" "320,907.4" "1" "1" "180")
(command "_insert" "blkuc1" "320,908.14" "1" "1" "0")
(command "_insert" "blkuc1" "320,907.77" "1" "1" "180")
(command "_insert" "blkuc1" "320,908.51" "1" "1" "0")
(command "_insert" "blkuc1" "320,908.14" "1" "1" "180")
(command "_insert" "blkuc1" "320,908.88" "1" "1" "0")
(command "_insert" "blkuc1" "320,908.51" "1" "1" "180")
(command "_insert" "blkuc1" "320,909.25" "1" "1" "0")
(command "_insert" "blkuc1" "320,908.88" "1" "1" "180")
(command "_insert" "blkuc1" "320,909.62" "1" "1" "0")
(command "_insert" "blkuc1" "320,909.25" "1" "1" "180")
(command "_insert" "blkuc1" "320,909.99" "1" "1" "0")
(command "_insert" "blkuc1" "320,909.62" "1" "1" "180")
(command "_insert" "blkuc1" "320,910.36" "1" "1" "0")
(command "_insert" "blkuc1" "320,909.99" "1" "1" "180")
(command "_insert" "blkuc1" "320,910.73" "1" "1" "0")
(command "_insert" "blkuc1" "320,910.36" "1" "1" "180")
(command "_insert" "blkuc1" "320,911.1" "1" "1" "0")
(command "_insert" "blkuc1" "320,910.73" "1" "1" "180")
(command "_insert" "blkuc1" "320,911.47" "1" "1" "0")
(command "_insert" "blkuc1" "320,911.1" "1" "1" "180")
(command "_insert" "blkuc1" "320,911.84" "1" "1" "0")
(command "_insert" "blkuc1" "320,911.47" "1" "1" "180")
(command "_insert" "blkuc1" "320,912.21" "1" "1" "0")
(command "_insert" "blkuc1" "320,911.84" "1" "1" "180")
(command "_insert" "blkuc1" "320,912.58" "1" "1" "0")
(command "_insert" "blkuc1" "320,912.21" "1" "1" "180")
(command "_insert" "blkuc1" "320,912.95" "1" "1" "0")
(command "_insert" "blkuc1" "320,912.58" "1" "1" "180")
(command "_insert" "blkuc1" "320,913.32" "1" "1" "0")
(command "_insert" "blkuc1" "320,912.95" "1" "1" "180")
(command "_insert" "blkuc1" "320,913.69" "1" "1" "0")
(command "_insert" "blkuc1" "320,913.32" "1" "1" "180")
(command "_insert" "blkuc1" "320,914.06" "1" "1" "0")
(command "_insert" "blkuc1" "320,913.69" "1" "1" "180")
(command "_insert" "blkuc1" "320,914.43" "1" "1" "0")
(command "_insert" "blkuc1" "320,914.06" "1" "1" "180")
(command "_insert" "blkuc1" "320,914.8" "1" "1" "0")
(command "_insert" "blkuc1" "320,914.43" "1" "1" "180")
(command "_insert" "blkuc1" "320,915.17" "1" "1" "0")
(command "_insert" "blkuc1" "320,914.8" "1" "1" "180")
(command "_insert" "blkuc1" "320,915.54" "1" "1" "0")
(command "_insert" "blkuc1" "320,915.17" "1" "1" "180")
(command "_insert" "blkuc1" "320,915.91" "1" "1" "0")
(command "_insert" "blkuc1" "320,915.54" "1" "1" "180")
(command "_insert" "blkuc1" "320,916.28" "1" "1" "0")
(command "_insert" "blkuc1" "320,915.91" "1" "1" "180")
(command "_insert" "blkuc1" "320,916.65" "1" "1" "0")
(command "_insert" "blkuc1" "320,916.28" "1" "1" "180")
(command "_insert" "blkuc1" "320,917.02" "1" "1" "0")
(command "_insert" "blkuc1" "320,916.65" "1" "1" "180")
(command "_insert" "blkuc1" "320,917.39" "1" "1" "0")
(command "_insert" "blkuc1" "320,917.02" "1" "1" "180")
(command "_insert" "blkuc1" "320,917.76" "1" "1" "0")
(command "_insert" "blkuc1" "320,917.39" "1" "1" "180")
(command "_insert" "blkuc1" "320,918.13" "1" "1" "0")
(command "_insert" "blkuc1" "320,917.76" "1" "1" "180")
(command "_insert" "blkuc1" "320,918.5" "1" "1" "0")
(command "_insert" "blkuc1" "320,918.13" "1" "1" "180")
(command "_insert" "blkuc1" "320,918.87" "1" "1" "0")
(command "_insert" "blkuc1" "320,918.5" "1" "1" "180")
(command "_insert" "blkuc1" "320,919.24" "1" "1" "0")
(command "_insert" "blkuc1" "320,918.87" "1" "1" "180")
(command "_insert" "blkuc1" "320,919.61" "1" "1" "0")
(command "_insert" "blkuc1" "320,919.24" "1" "1" "180")
(command "_insert" "blkuc1" "320,919.98" "1" "1" "0")
(command "_insert" "blkuc1" "320,919.61" "1" "1" "180")
(command "_insert" "blkuc1" "320,920.35" "1" "1" "0")
(command "_insert" "blkuc1" "320,919.98" "1" "1" "180")
(command "_insert" "blkuc1" "320,920.72" "1" "1" "0")
(command "_insert" "blkuc1" "320,920.35" "1" "1" "180")
(command "_insert" "blkuc1" "320,921.09" "1" "1" "0")
(command "_insert" "blkuc1" "320,920.72" "1" "1" "180")
(command "_insert" "blkuc1" "320,921.46" "1" "1" "0")
(command "_insert" "blkuc1" "320,921.09" "1" "1" "180")
(command "_insert" "blkuc1" "320,921.83" "1" "1" "0")
(command "_insert" "blkuc1" "320,921.46" "1" "1" "180")
(command "_insert" "blkuc1" "320,922.2" "1" "1" "0")
(command "_insert" "blkuc1" "320,921.83" "1" "1" "180")
(command "_insert" "blkuc1" "320,922.57" "1" "1" "0")
(command "_insert" "blkuc1" "320,922.2" "1" "1" "180")
(command "_insert" "blkuc1" "320,922.94" "1" "1" "0")
(command "_insert" "blkuc1" "320,922.57" "1" "1" "180")
(command "_insert" "blkuc1" "320,923.31" "1" "1" "0")
(command "_insert" "blkuc1" "320,922.94" "1" "1" "180")
(command "_insert" "blkuc1" "320,923.68" "1" "1" "0")
(command "_insert" "blkuc1" "320,923.31" "1" "1" "180")
(command "_insert" "blkuc1" "320,924.05" "1" "1" "0")
(command "_insert" "blkuc1" "320,923.68" "1" "1" "180")
(command "_insert" "blkuc1" "320,924.42" "1" "1" "0")
(command "_insert" "blkuc1" "320,924.05" "1" "1" "180")
(command "_insert" "blkuc1" "320,924.79" "1" "1" "0")
(command "_insert" "blkuc1" "320,924.42" "1" "1" "180")
(command "_insert" "blkuc1" "320,925.16" "1" "1" "0")
(command "_insert" "blkuc1" "320,924.79" "1" "1" "180")
(command "_insert" "blkuc1" "320,925.53" "1" "1" "0")
(command "_insert" "blkuc1" "320,925.16" "1" "1" "180")
(command "_insert" "blkuc1" "320,925.9" "1" "1" "0")
(command "_insert" "blkuc1" "320,925.53" "1" "1" "180")
(command "_insert" "blkuc1" "320,926.27" "1" "1" "0")
(command "_insert" "blkuc1" "320,925.9" "1" "1" "180")
(command "_insert" "blkuc1" "320,926.64" "1" "1" "0")
(command "_insert" "blkuc1" "320,926.27" "1" "1" "180")
(command "_insert" "blkuc1" "320,927.01" "1" "1" "0")
(command "_insert" "blkuc1" "320,926.64" "1" "1" "180")
(command "_insert" "blkuc1" "320,927.38" "1" "1" "0")
(command "_insert" "blkuc1" "320,927.01" "1" "1" "180")
(command "_insert" "blkuc1" "320,927.75" "1" "1" "0")
(command "_insert" "blkuc1" "320,927.38" "1" "1" "180")
(command "_layer" "set" "phccover" "")
(command "_rectangle" "318.878,933.3" "321.122,866.7")
(command "_layer" "set" "nitride" "")
(setq phc1 currobj)
(command "_layer" "set" "cover" "")
(command "_rectangle" "318.878,836.7" "321.122,963.3")
(command "_layer" "set" "nitride" "")
(command "_layer" "set" "text" "")
(command "_circle" "317.928,846.7" "0.075")
(command "_circle" "317.553,846.7" "0.15")
(command "_circle" "317.178,846.7" "0.075")
(command "_circle" "316.803,846.7" "0.15")
(command "_circle" "317.928,848.7" "0.075")
(command "_circle" "317.553,848.7" "0.075")
(command "_circle" "317.178,848.7" "0.15")
(command "_circle" "316.803,848.7" "0.15")
(command "_circle" "317.928,850.7" "0.075")
(command "_circle" "317.553,850.7" "0.15")
(command "_circle" "317.178,850.7" "0.15")
(command "_circle" "316.803,850.7" "0.15")
(command "_circle" "317.928,852.7" "0.075")
(command "_circle" "317.553,852.7" "0.075")
(command "_circle" "317.178,852.7" "0.075")
(command "_circle" "316.803,852.7" "0.075")
(command "_circle" "316.428,852.7" "0.15")
(command "_circle" "317.928,854.7" "0.075")
(command "_circle" "317.553,854.7" "0.15")
(command "_circle" "317.178,854.7" "0.075")
(command "_circle" "316.803,854.7" "0.075")
(command "_circle" "316.428,854.7" "0.15")
(command "_circle" "317.928,856.7" "0.075")
(command "_circle" "317.553,856.7" "0.075")
(command "_circle" "317.178,856.7" "0.15")
(command "_circle" "316.803,856.7" "0.075")
(command "_circle" "316.428,856.7" "0.15")
(command "_circle" "317.928,858.7" "0.075")
(command "_circle" "317.553,858.7" "0.15")
(command "_circle" "317.178,858.7" "0.15")
(command "_circle" "316.803,858.7" "0.075")
(command "_circle" "316.428,858.7" "0.15")
(command "_circle" "317.928,860.7" "0.075")
(command "_circle" "317.553,860.7" "0.075")
(command "_circle" "317.178,860.7" "0.075")
(command "_circle" "316.803,860.7" "0.15")
(command "_circle" "316.428,860.7" "0.15")
(command "_circle" "317.928,862.7" "0.075")
(command "_circle" "317.553,862.7" "0.15")
(command "_circle" "317.178,862.7" "0.075")
(command "_circle" "316.803,862.7" "0.15")
(command "_circle" "316.428,862.7" "0.15")
(command "_circle" "317.928,864.7" "0.075")
(command "_circle" "317.553,864.7" "0.075")
(command "_circle" "317.178,864.7" "0.15")
(command "_circle" "316.803,864.7" "0.15")
(command "_circle" "316.428,864.7" "0.15")
(command "_circle" "317.928,866.7" "0.075")
(command "_circle" "317.553,866.7" "0.15")
(command "_circle" "317.178,866.7" "0.15")
(command "_circle" "316.803,866.7" "0.15")
(command "_circle" "316.428,866.7" "0.15")
(command "_circle" "317.928,868.7" "0.075")
(command "_circle" "317.553,868.7" "0.075")
(command "_circle" "317.178,868.7" "0.075")
(command "_circle" "316.803,868.7" "0.075")
(command "_circle" "316.428,868.7" "0.075")
(command "_circle" "316.053,868.7" "0.15")
(command "_circle" "317.928,870.7" "0.075")
(command "_circle" "317.553,870.7" "0.15")
(command "_circle" "317.178,870.7" "0.075")
(command "_circle" "316.803,870.7" "0.075")
(command "_circle" "316.428,870.7" "0.075")
(command "_circle" "316.053,870.7" "0.15")
(command "_circle" "317.928,872.7" "0.075")
(command "_circle" "317.553,872.7" "0.075")
(command "_circle" "317.178,872.7" "0.15")
(command "_circle" "316.803,872.7" "0.075")
(command "_circle" "316.428,872.7" "0.075")
(command "_circle" "316.053,872.7" "0.15")
(command "_circle" "317.928,874.7" "0.075")
(command "_circle" "317.553,874.7" "0.15")
(command "_circle" "317.178,874.7" "0.15")
(command "_circle" "316.803,874.7" "0.075")
(command "_circle" "316.428,874.7" "0.075")
(command "_circle" "316.053,874.7" "0.15")
(command "_circle" "317.928,876.7" "0.075")
(command "_circle" "317.553,876.7" "0.075")
(command "_circle" "317.178,876.7" "0.075")
(command "_circle" "316.803,876.7" "0.15")
(command "_circle" "316.428,876.7" "0.075")
(command "_circle" "316.053,876.7" "0.15")
(command "_circle" "317.928,878.7" "0.075")
(command "_circle" "317.553,878.7" "0.15")
(command "_circle" "317.178,878.7" "0.075")
(command "_circle" "316.803,878.7" "0.15")
(command "_circle" "316.428,878.7" "0.075")
(command "_circle" "316.053,878.7" "0.15")
(command "_circle" "317.928,880.7" "0.075")
(command "_circle" "317.553,880.7" "0.075")
(command "_circle" "317.178,880.7" "0.15")
(command "_circle" "316.803,880.7" "0.15")
(command "_circle" "316.428,880.7" "0.075")
(command "_circle" "316.053,880.7" "0.15")
(command "_circle" "317.928,882.7" "0.075")
(command "_circle" "317.553,882.7" "0.15")
(command "_circle" "317.178,882.7" "0.15")
(command "_circle" "316.803,882.7" "0.15")
(command "_circle" "316.428,882.7" "0.075")
(command "_circle" "316.053,882.7" "0.15")
(command "_circle" "317.928,884.7" "0.075")
(command "_circle" "317.553,884.7" "0.075")
(command "_circle" "317.178,884.7" "0.075")
(command "_circle" "316.803,884.7" "0.075")
(command "_circle" "316.428,884.7" "0.15")
(command "_circle" "316.053,884.7" "0.15")
(command "_circle" "317.928,886.7" "0.075")
(command "_circle" "317.553,886.7" "0.15")
(command "_circle" "317.178,886.7" "0.075")
(command "_circle" "316.803,886.7" "0.075")
(command "_circle" "316.428,886.7" "0.15")
(command "_circle" "316.053,886.7" "0.15")
(command "_circle" "317.928,888.7" "0.075")
(command "_circle" "317.553,888.7" "0.075")
(command "_circle" "317.178,888.7" "0.15")
(command "_circle" "316.803,888.7" "0.075")
(command "_circle" "316.428,888.7" "0.15")
(command "_circle" "316.053,888.7" "0.15")
(command "_circle" "317.928,890.7" "0.075")
(command "_circle" "317.553,890.7" "0.15")
(command "_circle" "317.178,890.7" "0.15")
(command "_circle" "316.803,890.7" "0.075")
(command "_circle" "316.428,890.7" "0.15")
(command "_circle" "316.053,890.7" "0.15")
(command "_circle" "317.928,892.7" "0.075")
(command "_circle" "317.553,892.7" "0.075")
(command "_circle" "317.178,892.7" "0.075")
(command "_circle" "316.803,892.7" "0.15")
(command "_circle" "316.428,892.7" "0.15")
(command "_circle" "316.053,892.7" "0.15")
(command "_circle" "317.928,894.7" "0.075")
(command "_circle" "317.553,894.7" "0.15")
(command "_circle" "317.178,894.7" "0.075")
(command "_circle" "316.803,894.7" "0.15")
(command "_circle" "316.428,894.7" "0.15")
(command "_circle" "316.053,894.7" "0.15")
(command "_circle" "317.928,896.7" "0.075")
(command "_circle" "317.553,896.7" "0.075")
(command "_circle" "317.178,896.7" "0.15")
(command "_circle" "316.803,896.7" "0.15")
(command "_circle" "316.428,896.7" "0.15")
(command "_circle" "316.053,896.7" "0.15")
(command "_circle" "317.928,898.7" "0.075")
(command "_circle" "317.553,898.7" "0.15")
(command "_circle" "317.178,898.7" "0.15")
(command "_circle" "316.803,898.7" "0.15")
(command "_circle" "316.428,898.7" "0.15")
(command "_circle" "316.053,898.7" "0.15")
(command "_circle" "317.928,900.7" "0.075")
(command "_circle" "317.553,900.7" "0.075")
(command "_circle" "317.178,900.7" "0.075")
(command "_circle" "316.803,900.7" "0.075")
(command "_circle" "316.428,900.7" "0.075")
(command "_circle" "316.053,900.7" "0.075")
(command "_circle" "315.678,900.7" "0.15")
(command "_circle" "317.928,902.7" "0.075")
(command "_circle" "317.553,902.7" "0.15")
(command "_circle" "317.178,902.7" "0.075")
(command "_circle" "316.803,902.7" "0.075")
(command "_circle" "316.428,902.7" "0.075")
(command "_circle" "316.053,902.7" "0.075")
(command "_circle" "315.678,902.7" "0.15")
(command "_circle" "317.928,904.7" "0.075")
(command "_circle" "317.553,904.7" "0.075")
(command "_circle" "317.178,904.7" "0.15")
(command "_circle" "316.803,904.7" "0.075")
(command "_circle" "316.428,904.7" "0.075")
(command "_circle" "316.053,904.7" "0.075")
(command "_circle" "315.678,904.7" "0.15")
(command "_circle" "317.928,906.7" "0.075")
(command "_circle" "317.553,906.7" "0.15")
(command "_circle" "317.178,906.7" "0.15")
(command "_circle" "316.803,906.7" "0.075")
(command "_circle" "316.428,906.7" "0.075")
(command "_circle" "316.053,906.7" "0.075")
(command "_circle" "315.678,906.7" "0.15")
(command "_circle" "317.928,908.7" "0.075")
(command "_circle" "317.553,908.7" "0.075")
(command "_circle" "317.178,908.7" "0.075")
(command "_circle" "316.803,908.7" "0.15")
(command "_circle" "316.428,908.7" "0.075")
(command "_circle" "316.053,908.7" "0.075")
(command "_circle" "315.678,908.7" "0.15")
(command "_circle" "317.928,910.7" "0.075")
(command "_circle" "317.553,910.7" "0.15")
(command "_circle" "317.178,910.7" "0.075")
(command "_circle" "316.803,910.7" "0.15")
(command "_circle" "316.428,910.7" "0.075")
(command "_circle" "316.053,910.7" "0.075")
(command "_circle" "315.678,910.7" "0.15")
(command "_circle" "317.928,912.7" "0.075")
(command "_circle" "317.553,912.7" "0.075")
(command "_circle" "317.178,912.7" "0.15")
(command "_circle" "316.803,912.7" "0.15")
(command "_circle" "316.428,912.7" "0.075")
(command "_circle" "316.053,912.7" "0.075")
(command "_circle" "315.678,912.7" "0.15")
(command "_circle" "317.928,914.7" "0.075")
(command "_circle" "317.553,914.7" "0.15")
(command "_circle" "317.178,914.7" "0.15")
(command "_circle" "316.803,914.7" "0.15")
(command "_circle" "316.428,914.7" "0.075")
(command "_circle" "316.053,914.7" "0.075")
(command "_circle" "315.678,914.7" "0.15")
(command "_circle" "317.928,916.7" "0.075")
(command "_circle" "317.553,916.7" "0.075")
(command "_circle" "317.178,916.7" "0.075")
(command "_circle" "316.803,916.7" "0.075")
(command "_circle" "316.428,916.7" "0.15")
(command "_circle" "316.053,916.7" "0.075")
(command "_circle" "315.678,916.7" "0.15")
(command "_circle" "317.928,918.7" "0.075")
(command "_circle" "317.553,918.7" "0.15")
(command "_circle" "317.178,918.7" "0.075")
(command "_circle" "316.803,918.7" "0.075")
(command "_circle" "316.428,918.7" "0.15")
(command "_circle" "316.053,918.7" "0.075")
(command "_circle" "315.678,918.7" "0.15")
(command "_circle" "317.928,920.7" "0.075")
(command "_circle" "317.553,920.7" "0.075")
(command "_circle" "317.178,920.7" "0.15")
(command "_circle" "316.803,920.7" "0.075")
(command "_circle" "316.428,920.7" "0.15")
(command "_circle" "316.053,920.7" "0.075")
(command "_circle" "315.678,920.7" "0.15")
(command "_circle" "317.928,922.7" "0.075")
(command "_circle" "317.553,922.7" "0.15")
(command "_circle" "317.178,922.7" "0.15")
(command "_circle" "316.803,922.7" "0.075")
(command "_circle" "316.428,922.7" "0.15")
(command "_circle" "316.053,922.7" "0.075")
(command "_circle" "315.678,922.7" "0.15")
(command "_circle" "317.928,924.7" "0.075")
(command "_circle" "317.553,924.7" "0.075")
(command "_circle" "317.178,924.7" "0.075")
(command "_circle" "316.803,924.7" "0.15")
(command "_circle" "316.428,924.7" "0.15")
(command "_circle" "316.053,924.7" "0.075")
(command "_circle" "315.678,924.7" "0.15")
(command "_circle" "317.928,926.7" "0.075")
(command "_circle" "317.553,926.7" "0.15")
(command "_circle" "317.178,926.7" "0.075")
(command "_circle" "316.803,926.7" "0.15")
(command "_circle" "316.428,926.7" "0.15")
(command "_circle" "316.053,926.7" "0.075")
(command "_circle" "315.678,926.7" "0.15")
(command "_circle" "317.928,928.7" "0.075")
(command "_circle" "317.553,928.7" "0.075")
(command "_circle" "317.178,928.7" "0.15")
(command "_circle" "316.803,928.7" "0.15")
(command "_circle" "316.428,928.7" "0.15")
(command "_circle" "316.053,928.7" "0.075")
(command "_circle" "315.678,928.7" "0.15")
(command "_circle" "317.928,930.7" "0.075")
(command "_circle" "317.553,930.7" "0.15")
(command "_circle" "317.178,930.7" "0.15")
(command "_circle" "316.803,930.7" "0.15")
(command "_circle" "316.428,930.7" "0.15")
(command "_circle" "316.053,930.7" "0.075")
(command "_circle" "315.678,930.7" "0.15")
(command "_circle" "317.928,932.7" "0.075")
(command "_circle" "317.553,932.7" "0.075")
(command "_circle" "317.178,932.7" "0.075")
(command "_circle" "316.803,932.7" "0.075")
(command "_circle" "316.428,932.7" "0.075")
(command "_circle" "316.053,932.7" "0.15")
(command "_circle" "315.678,932.7" "0.15")
(command "_circle" "317.928,934.7" "0.075")
(command "_circle" "317.553,934.7" "0.15")
(command "_circle" "317.178,934.7" "0.075")
(command "_circle" "316.803,934.7" "0.075")
(command "_circle" "316.428,934.7" "0.075")
(command "_circle" "316.053,934.7" "0.15")
(command "_circle" "315.678,934.7" "0.15")
(command "_circle" "317.928,936.7" "0.075")
(command "_circle" "317.553,936.7" "0.075")
(command "_circle" "317.178,936.7" "0.15")
(command "_circle" "316.803,936.7" "0.075")
(command "_circle" "316.428,936.7" "0.075")
(command "_circle" "316.053,936.7" "0.15")
(command "_circle" "315.678,936.7" "0.15")
(command "_circle" "317.928,938.7" "0.075")
(command "_circle" "317.553,938.7" "0.15")
(command "_circle" "317.178,938.7" "0.15")
(command "_circle" "316.803,938.7" "0.075")
(command "_circle" "316.428,938.7" "0.075")
(command "_circle" "316.053,938.7" "0.15")
(command "_circle" "315.678,938.7" "0.15")
(command "_circle" "317.928,940.7" "0.075")
(command "_circle" "317.553,940.7" "0.075")
(command "_circle" "317.178,940.7" "0.075")
(command "_circle" "316.803,940.7" "0.15")
(command "_circle" "316.428,940.7" "0.075")
(command "_circle" "316.053,940.7" "0.15")
(command "_circle" "315.678,940.7" "0.15")
(command "_circle" "317.928,942.7" "0.075")
(command "_circle" "317.553,942.7" "0.15")
(command "_circle" "317.178,942.7" "0.075")
(command "_circle" "316.803,942.7" "0.15")
(command "_circle" "316.428,942.7" "0.075")
(command "_circle" "316.053,942.7" "0.15")
(command "_circle" "315.678,942.7" "0.15")
(command "_circle" "317.928,944.7" "0.075")
(command "_circle" "317.553,944.7" "0.075")
(command "_circle" "317.178,944.7" "0.15")
(command "_circle" "316.803,944.7" "0.15")
(command "_circle" "316.428,944.7" "0.075")
(command "_circle" "316.053,944.7" "0.15")
(command "_circle" "315.678,944.7" "0.15")
(command "_circle" "317.928,946.7" "0.075")
(command "_circle" "317.553,946.7" "0.15")
(command "_circle" "317.178,946.7" "0.15")
(command "_circle" "316.803,946.7" "0.15")
(command "_circle" "316.428,946.7" "0.075")
(command "_circle" "316.053,946.7" "0.15")
(command "_circle" "315.678,946.7" "0.15")
(command "_circle" "317.928,948.7" "0.075")
(command "_circle" "317.553,948.7" "0.075")
(command "_circle" "317.178,948.7" "0.075")
(command "_circle" "316.803,948.7" "0.075")
(command "_circle" "316.428,948.7" "0.15")
(command "_circle" "316.053,948.7" "0.15")
(command "_circle" "315.678,948.7" "0.15")
(command "_circle" "317.928,950.7" "0.075")
(command "_circle" "317.553,950.7" "0.15")
(command "_circle" "317.178,950.7" "0.075")
(command "_circle" "316.803,950.7" "0.075")
(command "_circle" "316.428,950.7" "0.15")
(command "_circle" "316.053,950.7" "0.15")
(command "_circle" "315.678,950.7" "0.15")
(command "_circle" "317.928,952.7" "0.075")
(command "_circle" "317.553,952.7" "0.075")
(command "_circle" "317.178,952.7" "0.15")
(command "_circle" "316.803,952.7" "0.075")
(command "_circle" "316.428,952.7" "0.15")
(command "_circle" "316.053,952.7" "0.15")
(command "_circle" "315.678,952.7" "0.15")
(command "_circle" "317.928,954.7" "0.075")
(command "_circle" "317.553,954.7" "0.15")
(command "_circle" "317.178,954.7" "0.15")
(command "_circle" "316.803,954.7" "0.075")
(command "_circle" "316.428,954.7" "0.15")
(command "_circle" "316.053,954.7" "0.15")
(command "_circle" "315.678,954.7" "0.15")
(command "_circle" "317.928,956.7" "0.075")
(command "_circle" "317.553,956.7" "0.075")
(command "_circle" "317.178,956.7" "0.075")
(command "_circle" "316.803,956.7" "0.15")
(command "_circle" "316.428,956.7" "0.15")
(command "_circle" "316.053,956.7" "0.15")
(command "_circle" "315.678,956.7" "0.15")
(command "_circle" "317.928,958.7" "0.075")
(command "_circle" "317.553,958.7" "0.15")
(command "_circle" "317.178,958.7" "0.075")
(command "_circle" "316.803,958.7" "0.15")
(command "_circle" "316.428,958.7" "0.15")
(command "_circle" "316.053,958.7" "0.15")
(command "_circle" "315.678,958.7" "0.15")
(command "_circle" "317.928,960.7" "0.075")
(command "_circle" "317.553,960.7" "0.075")
(command "_circle" "317.178,960.7" "0.15")
(command "_circle" "316.803,960.7" "0.15")
(command "_circle" "316.428,960.7" "0.15")
(command "_circle" "316.053,960.7" "0.15")
(command "_circle" "315.678,960.7" "0.15")
(command "_circle" "317.928,962.7" "0.075")
(command "_circle" "317.553,962.7" "0.15")
(command "_circle" "317.178,962.7" "0.15")
(command "_circle" "316.803,962.7" "0.15")
(command "_circle" "316.428,962.7" "0.15")
(command "_circle" "316.053,962.7" "0.15")
(command "_circle" "315.678,962.7" "0.15")
(command "_layer" "set" "nitride" "")
(command "_layer" "set" "text" "")
(command-s "_text" "306.878,963.3" "2" "-90" "a = 370 nm" )
(sssetfirst nil (ssget "_L"))
(if (not (numberp (vl-string-search "Mac" (getvar "platform")))) (c:txtexp))
(command "_layer" "set" "nitride" "")
(command "_layer" "set" "text" "")
(command-s "_text" "303.878,963.3" "2" "-90" "gap = 270 nm" )
(sssetfirst nil (ssget "_L"))
(if (not (numberp (vl-string-search "Mac" (getvar "platform")))) (c:txtexp))
(command "_layer" "set" "nitride" "")
(command "_layer" "set" "text" "")
(command-s "_text" "300.878,963.3" "2" "-90" "amplitude = 134 nm" )
(sssetfirst nil (ssget "_L"))
(if (not (numberp (vl-string-search "Mac" (getvar "platform")))) (c:txtexp))
(command "_layer" "set" "nitride" "")
(command "_layer" "set" "text" "")
(command-s "_text" "297.878,963.3" "2" "-90" "start width = 280 nm" )
(sssetfirst nil (ssget "_L"))
(if (not (numberp (vl-string-search "Mac" (getvar "platform")))) (c:txtexp))
(command "_layer" "set" "nitride" "")
(command "_layer" "set" "text" "")
(command-s "_text" "294.878,963.3" "2" "-90" "width = 292 nm" )
(sssetfirst nil (ssget "_L"))
(if (not (numberp (vl-string-search "Mac" (getvar "platform")))) (c:txtexp))
(command "_layer" "set" "nitride" "")
(command "_layer" "set" "text" "")
(command-s "_text" "291.878,963.3" "2" "-90" "taper: 15" )
(sssetfirst nil (ssget "_L"))
(if (not (numberp (vl-string-search "Mac" (getvar "platform")))) (c:txtexp))
(command "_layer" "set" "nitride" "")
(command "_layer" "set" "text" "")
(command-s "_text" "288.878,963.3" "2" "-90" "nominal: 150" )
(sssetfirst nil (ssget "_L"))
(if (not (numberp (vl-string-search "Mac" (getvar "platform")))) (c:txtexp))
(command "_layer" "set" "nitride" "")
(command "_layer" "set" "indicators" "")
(setq coords (list 
(list 240.415 940) 
(list 240.415 920) 
(list 220.415 900) 
(list 240.415 880) 
(list 240.415 860) 
(list 240.415 900) 
(list 240.415 887.0711) 
(list 227.4861 900) 
(list 240.415 912.9289) 
(list 240.415 900)))
(apply 'command (append '("pline") coords '("c")))
(command "._fillet" "radius" "1" "._fillet" "P" (entlast))
(setq coords (list 
(list 399.585 940) 
(list 399.585 920) 
(list 419.585 900) 
(list 399.585 880) 
(list 399.585 860) 
(list 399.585 900) 
(list 399.585 887.0711) 
(list 412.5139 900) 
(list 399.585 912.9289) 
(list 399.585 900)))
(apply 'command (append '("pline") coords '("c")))
(command "._fillet" "radius" "1" "._fillet" "P" (entlast))
(command "_layer" "set" "holes" "")
(command "_circle" "238.0629,914.1124" "0.5")
(command "_circle" "235.7109,911.7603" "0.5")
(command "_circle" "233.3588,909.4083" "0.5")
(command "_circle" "231.0067,907.0562" "0.5")
(command "_circle" "228.6547,904.7041" "0.5")
(command "_circle" "226.3026,902.3521" "0.5")
(command "_circle" "223.9505,900" "0.5")
(command "_circle" "226.3026,897.6479" "0.5")
(command "_circle" "228.6547,895.2959" "0.5")
(command "_circle" "231.0067,892.9438" "0.5")
(command "_circle" "233.3588,890.5917" "0.5")
(command "_circle" "235.7109,888.2397" "0.5")
(command "_circle" "238.0629,885.8876" "0.5")
(command "_circle" "401.9371,914.1124" "0.5")
(command "_circle" "404.2891,911.7603" "0.5")
(command "_circle" "406.6412,909.4083" "0.5")
(command "_circle" "408.9933,907.0562" "0.5")
(command "_circle" "411.3453,904.7041" "0.5")
(command "_circle" "413.6974,902.3521" "0.5")
(command "_circle" "416.0495,900" "0.5")
(command "_circle" "413.6974,897.6479" "0.5")
(command "_circle" "411.3453,895.2959" "0.5")
(command "_circle" "408.9933,892.9438" "0.5")
(command "_circle" "406.6412,890.5917" "0.5")
(command "_circle" "404.2891,888.2397" "0.5")
(command "_circle" "401.9371,885.8876" "0.5")
(command "_layer" "set" "nitride" "")
(command "_block" "blkcoupler1" "320,900" coupler1 "")
(command "_insert" "blkcoupler1" "320,900" "1" "1" "0")
(command "_insert" "blkcoupler1" "320,900" "1" "1" "180")
(command "_block" "blksinglenanobeam1" "320,900" singlenanobeam1 "")
(command "_insert" "blksinglenanobeam1" "320,900" "1" "1" "0")
(command "_insert" "blksinglenanobeam1" "320,900" "1" "1" "180")
(command "_block" "blkanglednodearray1" "320,900" anglednodearray1 "")
(command "_insert" "blkanglednodearray1" "320,900" "1" "1" "0")
(command "_insert" "blkanglednodearray1" "320,900" "1" "1" "180")
(command "_block" "blkcooledsinglenanobeam1" "320,900" cooledsinglenanobeam1 "")
(command "_insert" "blkcooledsinglenanobeam1" "320,900" "1" "1" "0")
(command "_insert" "blkcooledsinglenanobeam1" "320,900" "1" "1" "180")
(command "_block" "blkyjunction1" "320,900" yjunction1 "")
(command "_insert" "blkyjunction1" "320,900" "1" "1" "0")
(command "_insert" "blkyjunction1" "320,900" "1" "1" "180")
; DRAWING BULGING VEE GROOVE
(command "_layer" "set" "vgroove" "")
(setq coords (list 
(list 245.415 -605) 
(list 245.415 0) 
(list 245.415 0) 
(list 245.415 1800) 
(list 245.415 1800) 
(list 245.415 2405) 
(list 394.585 2405) 
(list 394.585 1800) 
(list 394.585 1800) 
(list 394.585 0) 
(list 394.585 0) 
(list 394.585 -605)))
(apply 'command (append '("pline") coords '("c")))
(command "._fillet" "radius" "0" "._fillet" "P" (entlast))
(command "_layer" "set" "window" "")
(command "_rectangle" "245.415,-1935" "394.585,-600")
(command "_rectangle" "245.415,2400" "394.585,5300")
(command "_layer" "set" "grid" "")
(command "_rectangle" "246.415,-1934" "269.9433,-1909.2133")
(command "_array" "last" "" "R" "75" "3" "25.7867" "24.5283")
(command "_rectangle" "321,-1934" "344.5283,-1909.2133")
(command "_array" "last" "" "R" "75" "3" "25.7867" "24.5283")
(command "_rectangle" "246.415,1" "269.9433,25.7")
(command "_array" "last" "" "R" "70" "3" "25.7" "24.5283")
(command "_rectangle" "321,1" "344.5283,25.7")
(command "_array" "last" "" "R" "70" "3" "25.7" "24.5283")
(command "_rectangle" "246.415,1801" "269.9433,1825.9185")
(command "_array" "last" "" "R" "135" "3" "25.9185" "24.5283")
(command "_rectangle" "321,1801" "344.5283,1825.9185")
(command "_array" "last" "" "R" "135" "3" "25.9185" "24.5283")
(command "_layer" "set" "vgrooveFDA" "")
(command "_rectangle" "394.585,-2233" "245.415,-1933")
(command "_layer" "set" "nitride" "")
(command "_layer" "set" "holes" "")
(command "_circle" "397.085,331.5" "0.5")
(command "_array" "last" "" "R" "379" "1" "3" "2.5")
(command "_circle" "242.915,331.5" "0.5")
(command "_array" "last" "" "R" "379" "1" "3" "-2.5")
(command "_layer" "set" "nitride" "")
(command "_layer" "set" "window" "")
(command "_layer" "set" "window" "")
(command "_rectangle" "240.415,0" "-986.225,1800")
(command "._fillet" "radius" "20" "._fillet" "P" (entlast))
(command "_layer" "set" "grid" "")
(command "_rectangle" "-985.225,1" "-960.6908,25.7")
(command "_array" "last" "" "R" "70" "48" "25.7" "25.5342")
(command "_layer" "set" "window" "")
(command "_rectangle" "399.585,0" "560.415,1800")
(command "._fillet" "radius" "20" "._fillet" "P" (entlast))
(command "_layer" "set" "grid" "")
(command "_rectangle" "400.585,1" "422.4179,25.7")
(command "_array" "last" "" "R" "70" "7" "25.7" "22.8329")
(command "_layer" "set" "nitride" "")
; DRAWING REGION LAYER
(command "_layer" "set" "regionLayer1" "")
(command "_rectangle" "240,-460" "400,2260")
(command "_layer" "set" "nitride" "")
(setq coupler1 nil)
(setq singlenanobeam1 nil)
(setq anglednodearray1 nil)
(setq cooledsinglenanobeam1 nil)
(setq yjunction1 nil)
; DEVICE #2
(command "_layer" "set" "window" "")
(command "_circle" "552.915,-415" "5")
(command "_circle" "552.915,-402.5" "5")
(command "_layer" "set" "nitride" "")
(setq currobj nil)
(setq currobj (ssadd))
; DRAWING COUPLER
(setq coords (list 
(list 640.0645 -415) 
(list 640.0645 -413) 
(list 713.585 -413) 
(list 713.585 -413) 
(list 713.9677 -413.0761) 
(list 714.2921 -413.2929) 
(list 714.5089 -413.6173) 
(list 714.585 -414) 
(list 714.585 -411.8) 
(list 714.585 -411.8) 
(list 714.5089 -412.1827) 
(list 714.2921 -412.5071) 
(list 713.9677 -412.7239) 
(list 713.585 -412.8) 
(list 640.0645 -412.8) 
(list 640.0645 -410.8) 
(list 639.9355 -410.8) 
(list 639.9355 -412.8) 
(list 566.415 -412.8) 
(list 566.0323 -412.7239) 
(list 565.7079 -412.5071) 
(list 565.4911 -412.1827) 
(list 565.415 -411.8) 
(list 565.415 -411.8) 
(list 565.415 -414) 
(list 565.4911 -413.6173) 
(list 565.7079 -413.2929) 
(list 566.0323 -413.0761) 
(list 566.415 -413) 
(list 566.415 -413) 
(list 639.9355 -413) 
(list 639.9355 -415)))
(apply 'command (append '("pline") coords '("c")))
(setq currobj (ssadd (entlast) currobj))
(command "._fillet" "radius" "0.3" "._fillet" "P" (entlast))
(command "_layer" "set" "holes" "")
(command "_circle" "640,-412.9" "0.113")
(setq currobj (ssadd (entlast) currobj))
(command "_layer" "set" "nitride" "")
(command "_layer" "set" "text" "")
(command "_circle" "639.2,-415" "0.075")
(command "_circle" "639.2,-414.7" "0.075")
(command "_circle" "639.2,-414.4" "0.075")
(command "_circle" "638.9,-415" "0.075")
(command "_circle" "638.9,-414.7" "0.075")
(command "_circle" "638.9,-414.4" "0.075")
(command "_circle" "638.6,-415" "0.075")
(command "_circle" "638.6,-414.7" "0.075")
(command "_circle" "638.6,-414.4" "0.075")
(command "_layer" "set" "nitride" "")
(command "_layer" "set" "prebias" "")
(command "_rectangle" "565.415,-414" "714.585,-411.8")
(setq currobj (ssadd (entlast) currobj))
(command "_rectangle" "639.9355,-415" "640.0645,-410.8")
(setq currobj (ssadd (entlast) currobj))
(command "_layer" "set" "nitride" "")
(setq coupler2 currobj)
(setq currobj nil)
(setq currobj (ssadd))
; DRAWING SINGLE NANOBEAM
(setq coords (list 
(list 640.0645 -410.8) 
(list 640.0645 -409.1417) 
(list 640.0645 -407.4833) 
(list 640.0645 -405.825) 
(list 640.0645 -404.1667) 
(list 640.0645 -402.5083) 
(list 640.0645 -400.85) 
(list 640.0645 -399.1917) 
(list 640.0645 -397.5333) 
(list 640.0646 -395.875) 
(list 640.0646 -394.2167) 
(list 640.0646 -392.5583) 
(list 640.0646 -390.9) 
(list 640.0647 -389.2417) 
(list 640.0647 -387.5833) 
(list 640.0647 -385.925) 
(list 640.0648 -384.2667) 
(list 640.0648 -382.6083) 
(list 640.0649 -380.95) 
(list 640.065 -379.2917) 
(list 640.0651 -377.6333) 
(list 640.0651 -375.975) 
(list 640.0652 -374.3167) 
(list 640.0653 -372.6583) 
(list 640.0655 -371) 
(list 640.0656 -369.3417) 
(list 640.0657 -367.6833) 
(list 640.0659 -366.025) 
(list 640.066 -364.3667) 
(list 640.0662 -362.7083) 
(list 640.0664 -361.05) 
(list 640.0666 -359.3917) 
(list 640.0668 -357.7333) 
(list 640.067 -356.075) 
(list 640.0672 -354.4167) 
(list 640.0675 -352.7583) 
(list 640.0678 -351.1) 
(list 640.068 -349.4417) 
(list 640.0683 -347.7833) 
(list 640.0686 -346.125) 
(list 640.069 -344.4667) 
(list 640.0693 -342.8083) 
(list 640.0697 -341.15) 
(list 640.07 -339.4917) 
(list 640.0704 -337.8333) 
(list 640.0709 -336.175) 
(list 640.0713 -334.5167) 
(list 640.0717 -332.8583) 
(list 640.0722 -331.2) 
(list 640.0727 -329.5417) 
(list 640.0732 -327.8833) 
(list 640.0738 -326.225) 
(list 640.0743 -324.5667) 
(list 640.0749 -322.9083) 
(list 640.0755 -321.25) 
(list 640.0761 -319.5917) 
(list 640.0767 -317.9333) 
(list 640.0774 -316.275) 
(list 640.0781 -314.6167) 
(list 640.0788 -312.9583) 
(list 640.0796 -311.3) 
(list 640.0803 -309.6417) 
(list 640.0811 -307.9833) 
(list 640.0819 -306.325) 
(list 640.0828 -304.6667) 
(list 640.0837 -303.0083) 
(list 640.0845 -301.35) 
(list 640.0855 -299.6917) 
(list 640.0864 -298.0333) 
(list 640.0874 -296.375) 
(list 640.0884 -294.7167) 
(list 640.0895 -293.0583) 
(list 640.0905 -291.4) 
(list 640.0916 -289.7417) 
(list 640.0928 -288.0833) 
(list 640.0939 -286.425) 
(list 640.0951 -284.7667) 
(list 640.0963 -283.1083) 
(list 640.0976 -281.45) 
(list 640.0989 -279.7917) 
(list 640.1002 -278.1333) 
(list 640.1016 -276.475) 
(list 640.1029 -274.8167) 
(list 640.1044 -273.1583) 
(list 640.1058 -271.5) 
(list 640.1073 -269.8417) 
(list 640.1089 -268.1833) 
(list 640.1104 -266.525) 
(list 640.112 -264.8667) 
(list 640.1137 -263.2083) 
(list 640.1153 -261.55) 
(list 640.117 -259.8917) 
(list 640.1188 -258.2333) 
(list 640.1206 -256.575) 
(list 640.1224 -254.9167) 
(list 640.1243 -253.2583) 
(list 640.1262 -251.6) 
(list 640.1281 -249.9417) 
(list 640.1301 -248.2833) 
(list 640.1322 -246.625) 
(list 640.1342 -244.9667) 
(list 640.1363 -243.3083) 
(list 640.1385 -241.65) 
(list 640.1407 -239.9917) 
(list 640.1429 -238.3333) 
(list 640.1452 -236.675) 
(list 640.1476 -235.0167) 
(list 640.1499 -233.3583) 
(list 640.1523 -231.7) 
(list 640.1548 -230.0417) 
(list 640.1573 -228.3833) 
(list 640.1599 -226.725) 
(list 640.1625 -225.0667) 
(list 640.1651 -223.4083) 
(list 640.1678 -221.75) 
(list 640.1706 -220.0917) 
(list 640.1733 -218.4333) 
(list 640.1762 -216.775) 
(list 640.1791 -215.1167) 
(list 640.182 -213.4583) 
(list 640.185 -211.8) 
(list 639.815 -211.8) 
(list 639.818 -213.4583) 
(list 639.8209 -215.1167) 
(list 639.8238 -216.775) 
(list 639.8267 -218.4333) 
(list 639.8294 -220.0917) 
(list 639.8322 -221.75) 
(list 639.8349 -223.4083) 
(list 639.8375 -225.0667) 
(list 639.8401 -226.725) 
(list 639.8427 -228.3833) 
(list 639.8452 -230.0417) 
(list 639.8477 -231.7) 
(list 639.8501 -233.3583) 
(list 639.8524 -235.0167) 
(list 639.8548 -236.675) 
(list 639.8571 -238.3333) 
(list 639.8593 -239.9917) 
(list 639.8615 -241.65) 
(list 639.8637 -243.3083) 
(list 639.8658 -244.9667) 
(list 639.8678 -246.625) 
(list 639.8699 -248.2833) 
(list 639.8719 -249.9417) 
(list 639.8738 -251.6) 
(list 639.8757 -253.2583) 
(list 639.8776 -254.9167) 
(list 639.8794 -256.575) 
(list 639.8812 -258.2333) 
(list 639.883 -259.8917) 
(list 639.8847 -261.55) 
(list 639.8863 -263.2083) 
(list 639.888 -264.8667) 
(list 639.8896 -266.525) 
(list 639.8911 -268.1833) 
(list 639.8927 -269.8417) 
(list 639.8942 -271.5) 
(list 639.8956 -273.1583) 
(list 639.8971 -274.8167) 
(list 639.8984 -276.475) 
(list 639.8998 -278.1333) 
(list 639.9011 -279.7917) 
(list 639.9024 -281.45) 
(list 639.9037 -283.1083) 
(list 639.9049 -284.7667) 
(list 639.9061 -286.425) 
(list 639.9072 -288.0833) 
(list 639.9084 -289.7417) 
(list 639.9095 -291.4) 
(list 639.9105 -293.0583) 
(list 639.9116 -294.7167) 
(list 639.9126 -296.375) 
(list 639.9136 -298.0333) 
(list 639.9145 -299.6917) 
(list 639.9155 -301.35) 
(list 639.9163 -303.0083) 
(list 639.9172 -304.6667) 
(list 639.9181 -306.325) 
(list 639.9189 -307.9833) 
(list 639.9197 -309.6417) 
(list 639.9204 -311.3) 
(list 639.9212 -312.9583) 
(list 639.9219 -314.6167) 
(list 639.9226 -316.275) 
(list 639.9233 -317.9333) 
(list 639.9239 -319.5917) 
(list 639.9245 -321.25) 
(list 639.9251 -322.9083) 
(list 639.9257 -324.5667) 
(list 639.9262 -326.225) 
(list 639.9268 -327.8833) 
(list 639.9273 -329.5417) 
(list 639.9278 -331.2) 
(list 639.9283 -332.8583) 
(list 639.9287 -334.5167) 
(list 639.9291 -336.175) 
(list 639.9296 -337.8333) 
(list 639.93 -339.4917) 
(list 639.9303 -341.15) 
(list 639.9307 -342.8083) 
(list 639.931 -344.4667) 
(list 639.9314 -346.125) 
(list 639.9317 -347.7833) 
(list 639.932 -349.4417) 
(list 639.9322 -351.1) 
(list 639.9325 -352.7583) 
(list 639.9328 -354.4167) 
(list 639.933 -356.075) 
(list 639.9332 -357.7333) 
(list 639.9334 -359.3917) 
(list 639.9336 -361.05) 
(list 639.9338 -362.7083) 
(list 639.934 -364.3667) 
(list 639.9341 -366.025) 
(list 639.9343 -367.6833) 
(list 639.9344 -369.3417) 
(list 639.9345 -371) 
(list 639.9347 -372.6583) 
(list 639.9348 -374.3167) 
(list 639.9349 -375.975) 
(list 639.9349 -377.6333) 
(list 639.935 -379.2917) 
(list 639.9351 -380.95) 
(list 639.9352 -382.6083) 
(list 639.9352 -384.2667) 
(list 639.9353 -385.925) 
(list 639.9353 -387.5833) 
(list 639.9353 -389.2417) 
(list 639.9354 -390.9) 
(list 639.9354 -392.5583) 
(list 639.9354 -394.2167) 
(list 639.9354 -395.875) 
(list 639.9355 -397.5333) 
(list 639.9355 -399.1917) 
(list 639.9355 -400.85) 
(list 639.9355 -402.5083) 
(list 639.9355 -404.1667) 
(list 639.9355 -405.825) 
(list 639.9355 -407.4833) 
(list 639.9355 -409.1417) 
(list 639.9355 -410.8)))
(apply 'command (append '("pline") coords '("c")))
(setq currobj (ssadd (entlast) currobj))
(command "_layer" "set" "prebias" "")
(command "_rectangle" "639.815,-410.8" "640.185,-211.8")
(setq currobj (ssadd (entlast) currobj))
(command "_layer" "set" "nitride" "")
(setq singlenanobeam2 currobj)
(setq currobj nil)
(setq currobj (ssadd))
; DRAWING NODE ARRAY
(setq coords (list 
(list 640.185 -211.8) 
(list 640.5625 -201.8) 
(list 640.5625 -201.8) 
(list 640.5625 -200.8) 
(list 714.585 -212.6864) 
(list 714.585 -207.7434) 
(list 640.5625 -197.357) 
(list 640.5625 -196.357) 
(list 640.5625 -196.357) 
(list 640.2625 -186.357) 
(list 639.7375 -186.357) 
(list 639.4375 -196.357) 
(list 639.4375 -196.357) 
(list 639.4375 -197.357) 
(list 565.415 -207.7434) 
(list 565.415 -212.6864) 
(list 639.4375 -200.8) 
(list 639.4375 -201.8) 
(list 639.4375 -201.8) 
(list 639.815 -211.8)))
(apply 'command (append '("pline") coords '("c")))
(setq currobj (ssadd (entlast) currobj))
(command "_layer" "set" "prebias" "")
(setq coords (list 
(list 639.4375 -212.6864) 
(list 639.4375 -200.8) 
(list 565.415 -212.6864) 
(list 565.415 -207.7434) 
(list 639.4375 -197.357) 
(list 639.4375 -186.357) 
(list 640.5625 -186.357) 
(list 640.5625 -197.357) 
(list 714.585 -207.7434) 
(list 714.585 -212.6864) 
(list 640.5625 -200.8) 
(list 640.5625 -212.6864)))
(apply 'command (append '("pline") coords '("c")))
(setq currobj (ssadd (entlast) currobj))
(command "_layer" "set" "nitride" "")
(command "_layer" "set" "fda1" "")
(setq coords (list 
(list 640.5625 -200.657) 
(list 714.585 -212.5434) 
(list 714.585 -212.3664) 
(list 640.5625 -200.58)))
(apply 'command (append '("pline") coords '("c")))
(setq currobj (ssadd (entlast) currobj))
(setq coords (list 
(list 640.5625 -200.437) 
(list 714.585 -212.2234) 
(list 714.585 -212.0464) 
(list 640.5625 -200.36)))
(apply 'command (append '("pline") coords '("c")))
(setq currobj (ssadd (entlast) currobj))
(setq coords (list 
(list 640.5625 -200.217) 
(list 714.585 -211.9034) 
(list 714.585 -211.7264) 
(list 640.5625 -200.14)))
(apply 'command (append '("pline") coords '("c")))
(setq currobj (ssadd (entlast) currobj))
(setq coords (list 
(list 640.5625 -199.997) 
(list 714.585 -211.5834) 
(list 714.585 -211.4064) 
(list 640.5625 -199.92)))
(apply 'command (append '("pline") coords '("c")))
(setq currobj (ssadd (entlast) currobj))
(setq coords (list 
(list 640.5625 -199.777) 
(list 714.585 -211.2634) 
(list 714.585 -211.0864) 
(list 640.5625 -199.7)))
(apply 'command (append '("pline") coords '("c")))
(setq currobj (ssadd (entlast) currobj))
(setq coords (list 
(list 640.5625 -199.557) 
(list 714.585 -210.9434) 
(list 714.585 -210.7664) 
(list 640.5625 -199.48)))
(apply 'command (append '("pline") coords '("c")))
(setq currobj (ssadd (entlast) currobj))
(setq coords (list 
(list 640.5625 -199.337) 
(list 714.585 -210.6234) 
(list 714.585 -210.4464) 
(list 640.5625 -199.26)))
(apply 'command (append '("pline") coords '("c")))
(setq currobj (ssadd (entlast) currobj))
(setq coords (list 
(list 640.5625 -199.117) 
(list 714.585 -210.3034) 
(list 714.585 -210.1264) 
(list 640.5625 -199.04)))
(apply 'command (append '("pline") coords '("c")))
(setq currobj (ssadd (entlast) currobj))
(setq coords (list 
(list 640.5625 -198.897) 
(list 714.585 -209.9834) 
(list 714.585 -209.8064) 
(list 640.5625 -198.82)))
(apply 'command (append '("pline") coords '("c")))
(setq currobj (ssadd (entlast) currobj))
(setq coords (list 
(list 640.5625 -198.677) 
(list 714.585 -209.6634) 
(list 714.585 -209.4864) 
(list 640.5625 -198.6)))
(apply 'command (append '("pline") coords '("c")))
(setq currobj (ssadd (entlast) currobj))
(setq coords (list 
(list 640.5625 -198.457) 
(list 714.585 -209.3434) 
(list 714.585 -209.1664) 
(list 640.5625 -198.38)))
(apply 'command (append '("pline") coords '("c")))
(setq currobj (ssadd (entlast) currobj))
(setq coords (list 
(list 640.5625 -198.237) 
(list 714.585 -209.0234) 
(list 714.585 -208.8464) 
(list 640.5625 -198.16)))
(apply 'command (append '("pline") coords '("c")))
(setq currobj (ssadd (entlast) currobj))
(setq coords (list 
(list 640.5625 -198.017) 
(list 714.585 -208.7034) 
(list 714.585 -208.5264) 
(list 640.5625 -197.94)))
(apply 'command (append '("pline") coords '("c")))
(setq currobj (ssadd (entlast) currobj))
(setq coords (list 
(list 640.5625 -197.797) 
(list 714.585 -208.3834) 
(list 714.585 -208.2064) 
(list 640.5625 -197.72)))
(apply 'command (append '("pline") coords '("c")))
(setq currobj (ssadd (entlast) currobj))
(setq coords (list 
(list 640.5625 -197.577) 
(list 714.585 -208.0634) 
(list 714.585 -207.8864) 
(list 640.5625 -197.5)))
(apply 'command (append '("pline") coords '("c")))
(setq currobj (ssadd (entlast) currobj))
(setq coords (list 
(list 639.4375 -197.5) 
(list 565.415 -207.8864) 
(list 565.415 -208.0634) 
(list 639.4375 -197.577)))
(apply 'command (append '("pline") coords '("c")))
(setq currobj (ssadd (entlast) currobj))
(setq coords (list 
(list 639.4375 -197.72) 
(list 565.415 -208.2064) 
(list 565.415 -208.3834) 
(list 639.4375 -197.797)))
(apply 'command (append '("pline") coords '("c")))
(setq currobj (ssadd (entlast) currobj))
(setq coords (list 
(list 639.4375 -197.94) 
(list 565.415 -208.5264) 
(list 565.415 -208.7034) 
(list 639.4375 -198.017)))
(apply 'command (append '("pline") coords '("c")))
(setq currobj (ssadd (entlast) currobj))
(setq coords (list 
(list 639.4375 -198.16) 
(list 565.415 -208.8464) 
(list 565.415 -209.0234) 
(list 639.4375 -198.237)))
(apply 'command (append '("pline") coords '("c")))
(setq currobj (ssadd (entlast) currobj))
(setq coords (list 
(list 639.4375 -198.38) 
(list 565.415 -209.1664) 
(list 565.415 -209.3434) 
(list 639.4375 -198.457)))
(apply 'command (append '("pline") coords '("c")))
(setq currobj (ssadd (entlast) currobj))
(setq coords (list 
(list 639.4375 -198.6) 
(list 565.415 -209.4864) 
(list 565.415 -209.6634) 
(list 639.4375 -198.677)))
(apply 'command (append '("pline") coords '("c")))
(setq currobj (ssadd (entlast) currobj))
(setq coords (list 
(list 639.4375 -198.82) 
(list 565.415 -209.8064) 
(list 565.415 -209.9834) 
(list 639.4375 -198.897)))
(apply 'command (append '("pline") coords '("c")))
(setq currobj (ssadd (entlast) currobj))
(setq coords (list 
(list 639.4375 -199.04) 
(list 565.415 -210.1264) 
(list 565.415 -210.3034) 
(list 639.4375 -199.117)))
(apply 'command (append '("pline") coords '("c")))
(setq currobj (ssadd (entlast) currobj))
(setq coords (list 
(list 639.4375 -199.26) 
(list 565.415 -210.4464) 
(list 565.415 -210.6234) 
(list 639.4375 -199.337)))
(apply 'command (append '("pline") coords '("c")))
(setq currobj (ssadd (entlast) currobj))
(setq coords (list 
(list 639.4375 -199.48) 
(list 565.415 -210.7664) 
(list 565.415 -210.9434) 
(list 639.4375 -199.557)))
(apply 'command (append '("pline") coords '("c")))
(setq currobj (ssadd (entlast) currobj))
(setq coords (list 
(list 639.4375 -199.7) 
(list 565.415 -211.0864) 
(list 565.415 -211.2634) 
(list 639.4375 -199.777)))
(apply 'command (append '("pline") coords '("c")))
(setq currobj (ssadd (entlast) currobj))
(setq coords (list 
(list 639.4375 -199.92) 
(list 565.415 -211.4064) 
(list 565.415 -211.5834) 
(list 639.4375 -199.997)))
(apply 'command (append '("pline") coords '("c")))
(setq currobj (ssadd (entlast) currobj))
(setq coords (list 
(list 639.4375 -200.14) 
(list 565.415 -211.7264) 
(list 565.415 -211.9034) 
(list 639.4375 -200.217)))
(apply 'command (append '("pline") coords '("c")))
(setq currobj (ssadd (entlast) currobj))
(setq coords (list 
(list 639.4375 -200.36) 
(list 565.415 -212.0464) 
(list 565.415 -212.2234) 
(list 639.4375 -200.437)))
(apply 'command (append '("pline") coords '("c")))
(setq currobj (ssadd (entlast) currobj))
(setq coords (list 
(list 639.4375 -200.58) 
(list 565.415 -212.3664) 
(list 565.415 -212.5434) 
(list 639.4375 -200.657)))
(apply 'command (append '("pline") coords '("c")))
(setq currobj (ssadd (entlast) currobj))
(command "_layer" "set" "nitride" "")
(command "_layer" "set" "text" "")
(command "_circle" "638.985,-211.8" "0.075")
(command "_circle" "638.985,-211.5" "0.075")
(command "_circle" "638.985,-211.2" "0.075")
(command "_circle" "638.985,-210.9" "0.075")
(command "_circle" "638.985,-210.6" "0.075")
(command "_circle" "638.685,-211.8" "0.075")
(command "_circle" "638.685,-211.5" "0.075")
(command "_circle" "638.685,-211.2" "0.075")
(command "_circle" "638.685,-210.9" "0.075")
(command "_circle" "638.685,-210.6" "0.075")
(command "_circle" "638.385,-211.8" "0.075")
(command "_circle" "638.385,-211.5" "0.075")
(command "_circle" "638.385,-211.2" "0.075")
(command "_circle" "638.385,-210.9" "0.075")
(command "_circle" "638.385,-210.6" "0.075")
(command "_circle" "638.085,-211.8" "0.075")
(command "_circle" "638.085,-211.5" "0.075")
(command "_circle" "638.085,-211.2" "0.075")
(command "_circle" "638.085,-210.9" "0.075")
(command "_circle" "638.085,-210.6" "0.075")
(command "_circle" "637.785,-211.8" "0.075")
(command "_circle" "637.785,-211.5" "0.075")
(command "_circle" "637.785,-211.2" "0.075")
(command "_circle" "637.785,-210.9" "0.075")
(command "_circle" "637.785,-210.6" "0.075")
(command "_layer" "set" "nitride" "")
(setq anglednodearray2 currobj)
(setq currobj nil)
(setq currobj (ssadd))
; DRAWING COOLED SINGLE NANOBEAM
(setq coords (list 
(list 640.2625 -186.357) 
(list 640.2625 -181.357) 
(list 639.7375 -181.357) 
(list 639.7375 -186.357)))
(apply 'command (append '("pline") coords '("c")))
(setq currobj (ssadd (entlast) currobj))
(command "_layer" "set" "prebias" "")
(command "_rectangle" "639.7375,-186.357" "640.2625,-181.357")
(setq currobj (ssadd (entlast) currobj))
(command "_layer" "set" "nitride" "")
(setq coords (list 
(list 640.2625 -181.357) 
(list 640.5625 -171.357) 
(list 640.5625 -171.357) 
(list 640.5625 -170.357) 
(list 714.585 -171.107) 
(list 714.585 -166.164) 
(list 640.5625 -166.914) 
(list 640.5625 -165.914) 
(list 640.5625 -165.914) 
(list 640.2625 -155.914) 
(list 639.7375 -155.914) 
(list 639.4375 -165.914) 
(list 639.4375 -165.914) 
(list 639.4375 -166.914) 
(list 565.415 -166.164) 
(list 565.415 -171.107) 
(list 639.4375 -170.357) 
(list 639.4375 -171.357) 
(list 639.4375 -171.357) 
(list 639.7375 -181.357)))
(apply 'command (append '("pline") coords '("c")))
(setq currobj (ssadd (entlast) currobj))
(command "_layer" "set" "prebias" "")
(setq coords (list 
(list 639.4375 -181.357) 
(list 639.4375 -170.357) 
(list 565.415 -171.107) 
(list 565.415 -166.164) 
(list 639.4375 -166.914) 
(list 639.4375 -155.914) 
(list 640.5625 -155.914) 
(list 640.5625 -166.914) 
(list 714.585 -166.164) 
(list 714.585 -171.107) 
(list 640.5625 -170.357) 
(list 640.5625 -181.357)))
(apply 'command (append '("pline") coords '("c")))
(setq currobj (ssadd (entlast) currobj))
(command "_layer" "set" "nitride" "")
(command "_layer" "set" "fda1" "")
(setq coords (list 
(list 640.5625 -170.214) 
(list 714.585 -170.964) 
(list 714.585 -170.787) 
(list 640.5625 -170.137)))
(apply 'command (append '("pline") coords '("c")))
(setq currobj (ssadd (entlast) currobj))
(setq coords (list 
(list 640.5625 -169.994) 
(list 714.585 -170.644) 
(list 714.585 -170.467) 
(list 640.5625 -169.917)))
(apply 'command (append '("pline") coords '("c")))
(setq currobj (ssadd (entlast) currobj))
(setq coords (list 
(list 640.5625 -169.774) 
(list 714.585 -170.324) 
(list 714.585 -170.147) 
(list 640.5625 -169.697)))
(apply 'command (append '("pline") coords '("c")))
(setq currobj (ssadd (entlast) currobj))
(setq coords (list 
(list 640.5625 -169.554) 
(list 714.585 -170.004) 
(list 714.585 -169.827) 
(list 640.5625 -169.477)))
(apply 'command (append '("pline") coords '("c")))
(setq currobj (ssadd (entlast) currobj))
(setq coords (list 
(list 640.5625 -169.334) 
(list 714.585 -169.684) 
(list 714.585 -169.507) 
(list 640.5625 -169.257)))
(apply 'command (append '("pline") coords '("c")))
(setq currobj (ssadd (entlast) currobj))
(setq coords (list 
(list 640.5625 -169.114) 
(list 714.585 -169.364) 
(list 714.585 -169.187) 
(list 640.5625 -169.037)))
(apply 'command (append '("pline") coords '("c")))
(setq currobj (ssadd (entlast) currobj))
(setq coords (list 
(list 640.5625 -168.894) 
(list 714.585 -169.044) 
(list 714.585 -168.867) 
(list 640.5625 -168.817)))
(apply 'command (append '("pline") coords '("c")))
(setq currobj (ssadd (entlast) currobj))
(setq coords (list 
(list 640.5625 -168.674) 
(list 714.585 -168.724) 
(list 714.585 -168.547) 
(list 640.5625 -168.597)))
(apply 'command (append '("pline") coords '("c")))
(setq currobj (ssadd (entlast) currobj))
(setq coords (list 
(list 640.5625 -168.454) 
(list 714.585 -168.404) 
(list 714.585 -168.227) 
(list 640.5625 -168.377)))
(apply 'command (append '("pline") coords '("c")))
(setq currobj (ssadd (entlast) currobj))
(setq coords (list 
(list 640.5625 -168.234) 
(list 714.585 -168.084) 
(list 714.585 -167.907) 
(list 640.5625 -168.157)))
(apply 'command (append '("pline") coords '("c")))
(setq currobj (ssadd (entlast) currobj))
(setq coords (list 
(list 640.5625 -168.014) 
(list 714.585 -167.764) 
(list 714.585 -167.587) 
(list 640.5625 -167.937)))
(apply 'command (append '("pline") coords '("c")))
(setq currobj (ssadd (entlast) currobj))
(setq coords (list 
(list 640.5625 -167.794) 
(list 714.585 -167.444) 
(list 714.585 -167.267) 
(list 640.5625 -167.717)))
(apply 'command (append '("pline") coords '("c")))
(setq currobj (ssadd (entlast) currobj))
(setq coords (list 
(list 640.5625 -167.574) 
(list 714.585 -167.124) 
(list 714.585 -166.947) 
(list 640.5625 -167.497)))
(apply 'command (append '("pline") coords '("c")))
(setq currobj (ssadd (entlast) currobj))
(setq coords (list 
(list 640.5625 -167.354) 
(list 714.585 -166.804) 
(list 714.585 -166.627) 
(list 640.5625 -167.277)))
(apply 'command (append '("pline") coords '("c")))
(setq currobj (ssadd (entlast) currobj))
(setq coords (list 
(list 640.5625 -167.134) 
(list 714.585 -166.484) 
(list 714.585 -166.307) 
(list 640.5625 -167.057)))
(apply 'command (append '("pline") coords '("c")))
(setq currobj (ssadd (entlast) currobj))
(setq coords (list 
(list 639.4375 -167.057) 
(list 565.415 -166.307) 
(list 565.415 -166.484) 
(list 639.4375 -167.134)))
(apply 'command (append '("pline") coords '("c")))
(setq currobj (ssadd (entlast) currobj))
(setq coords (list 
(list 639.4375 -167.277) 
(list 565.415 -166.627) 
(list 565.415 -166.804) 
(list 639.4375 -167.354)))
(apply 'command (append '("pline") coords '("c")))
(setq currobj (ssadd (entlast) currobj))
(setq coords (list 
(list 639.4375 -167.497) 
(list 565.415 -166.947) 
(list 565.415 -167.124) 
(list 639.4375 -167.574)))
(apply 'command (append '("pline") coords '("c")))
(setq currobj (ssadd (entlast) currobj))
(setq coords (list 
(list 639.4375 -167.717) 
(list 565.415 -167.267) 
(list 565.415 -167.444) 
(list 639.4375 -167.794)))
(apply 'command (append '("pline") coords '("c")))
(setq currobj (ssadd (entlast) currobj))
(setq coords (list 
(list 639.4375 -167.937) 
(list 565.415 -167.587) 
(list 565.415 -167.764) 
(list 639.4375 -168.014)))
(apply 'command (append '("pline") coords '("c")))
(setq currobj (ssadd (entlast) currobj))
(setq coords (list 
(list 639.4375 -168.157) 
(list 565.415 -167.907) 
(list 565.415 -168.084) 
(list 639.4375 -168.234)))
(apply 'command (append '("pline") coords '("c")))
(setq currobj (ssadd (entlast) currobj))
(setq coords (list 
(list 639.4375 -168.377) 
(list 565.415 -168.227) 
(list 565.415 -168.404) 
(list 639.4375 -168.454)))
(apply 'command (append '("pline") coords '("c")))
(setq currobj (ssadd (entlast) currobj))
(setq coords (list 
(list 639.4375 -168.597) 
(list 565.415 -168.547) 
(list 565.415 -168.724) 
(list 639.4375 -168.674)))
(apply 'command (append '("pline") coords '("c")))
(setq currobj (ssadd (entlast) currobj))
(setq coords (list 
(list 639.4375 -168.817) 
(list 565.415 -168.867) 
(list 565.415 -169.044) 
(list 639.4375 -168.894)))
(apply 'command (append '("pline") coords '("c")))
(setq currobj (ssadd (entlast) currobj))
(setq coords (list 
(list 639.4375 -169.037) 
(list 565.415 -169.187) 
(list 565.415 -169.364) 
(list 639.4375 -169.114)))
(apply 'command (append '("pline") coords '("c")))
(setq currobj (ssadd (entlast) currobj))
(setq coords (list 
(list 639.4375 -169.257) 
(list 565.415 -169.507) 
(list 565.415 -169.684) 
(list 639.4375 -169.334)))
(apply 'command (append '("pline") coords '("c")))
(setq currobj (ssadd (entlast) currobj))
(setq coords (list 
(list 639.4375 -169.477) 
(list 565.415 -169.827) 
(list 565.415 -170.004) 
(list 639.4375 -169.554)))
(apply 'command (append '("pline") coords '("c")))
(setq currobj (ssadd (entlast) currobj))
(setq coords (list 
(list 639.4375 -169.697) 
(list 565.415 -170.147) 
(list 565.415 -170.324) 
(list 639.4375 -169.774)))
(apply 'command (append '("pline") coords '("c")))
(setq currobj (ssadd (entlast) currobj))
(setq coords (list 
(list 639.4375 -169.917) 
(list 565.415 -170.467) 
(list 565.415 -170.644) 
(list 639.4375 -169.994)))
(apply 'command (append '("pline") coords '("c")))
(setq currobj (ssadd (entlast) currobj))
(setq coords (list 
(list 639.4375 -170.137) 
(list 565.415 -170.787) 
(list 565.415 -170.964) 
(list 639.4375 -170.214)))
(apply 'command (append '("pline") coords '("c")))
(setq currobj (ssadd (entlast) currobj))
(command "_layer" "set" "nitride" "")
(command "_layer" "set" "text" "")
(command "_circle" "639.0625,-181.357" "0.075")
(command "_circle" "639.0625,-181.057" "0.075")
(command "_circle" "639.0625,-180.757" "0.075")
(command "_circle" "639.0625,-180.457" "0.075")
(command "_circle" "639.0625,-180.157" "0.075")
(command "_circle" "638.7625,-181.357" "0.075")
(command "_circle" "638.7625,-181.057" "0.075")
(command "_circle" "638.7625,-180.757" "0.075")
(command "_circle" "638.7625,-180.457" "0.075")
(command "_circle" "638.7625,-180.157" "0.075")
(command "_circle" "638.4625,-181.357" "0.075")
(command "_circle" "638.4625,-181.057" "0.075")
(command "_circle" "638.4625,-180.757" "0.075")
(command "_circle" "638.4625,-180.457" "0.075")
(command "_circle" "638.4625,-180.157" "0.075")
(command "_circle" "638.1625,-181.357" "0.075")
(command "_circle" "638.1625,-181.057" "0.075")
(command "_circle" "638.1625,-180.757" "0.075")
(command "_circle" "638.1625,-180.457" "0.075")
(command "_circle" "638.1625,-180.157" "0.075")
(command "_circle" "637.8625,-181.357" "0.075")
(command "_circle" "637.8625,-181.057" "0.075")
(command "_circle" "637.8625,-180.757" "0.075")
(command "_circle" "637.8625,-180.457" "0.075")
(command "_circle" "637.8625,-180.157" "0.075")
(command "_layer" "set" "nitride" "")
(setq coords (list 
(list 640.2625 -155.914) 
(list 640.2625 -40.2693) 
(list 639.7375 -40.2693) 
(list 639.7375 -155.914)))
(apply 'command (append '("pline") coords '("c")))
(setq currobj (ssadd (entlast) currobj))
(command "_layer" "set" "prebias" "")
(command "_rectangle" "639.7375,-155.914" "640.2625,-40.2693")
(setq currobj (ssadd (entlast) currobj))
(command "_layer" "set" "nitride" "")
(setq coords (list 
(list 640.2625 -40.2693) 
(list 640.5625 -30.2693) 
(list 640.5625 -30.2693) 
(list 640.5625 -29.2693) 
(list 714.585 -30.0193) 
(list 714.585 -25.0763) 
(list 640.5625 -25.8263) 
(list 640.5625 -24.8263) 
(list 640.5625 -24.8263) 
(list 640.2625 -14.8263) 
(list 639.7375 -14.8263) 
(list 639.4375 -24.8263) 
(list 639.4375 -24.8263) 
(list 639.4375 -25.8263) 
(list 565.415 -25.0763) 
(list 565.415 -30.0193) 
(list 639.4375 -29.2693) 
(list 639.4375 -30.2693) 
(list 639.4375 -30.2693) 
(list 639.7375 -40.2693)))
(apply 'command (append '("pline") coords '("c")))
(setq currobj (ssadd (entlast) currobj))
(command "_layer" "set" "prebias" "")
(setq coords (list 
(list 639.4375 -40.2693) 
(list 639.4375 -29.2693) 
(list 565.415 -30.0193) 
(list 565.415 -25.0763) 
(list 639.4375 -25.8263) 
(list 639.4375 -14.8263) 
(list 640.5625 -14.8263) 
(list 640.5625 -25.8263) 
(list 714.585 -25.0763) 
(list 714.585 -30.0193) 
(list 640.5625 -29.2693) 
(list 640.5625 -40.2693)))
(apply 'command (append '("pline") coords '("c")))
(setq currobj (ssadd (entlast) currobj))
(command "_layer" "set" "nitride" "")
(command "_layer" "set" "fda1" "")
(setq coords (list 
(list 640.5625 -29.1263) 
(list 714.585 -29.8763) 
(list 714.585 -29.6993) 
(list 640.5625 -29.0493)))
(apply 'command (append '("pline") coords '("c")))
(setq currobj (ssadd (entlast) currobj))
(setq coords (list 
(list 640.5625 -28.9063) 
(list 714.585 -29.5563) 
(list 714.585 -29.3793) 
(list 640.5625 -28.8293)))
(apply 'command (append '("pline") coords '("c")))
(setq currobj (ssadd (entlast) currobj))
(setq coords (list 
(list 640.5625 -28.6863) 
(list 714.585 -29.2363) 
(list 714.585 -29.0593) 
(list 640.5625 -28.6093)))
(apply 'command (append '("pline") coords '("c")))
(setq currobj (ssadd (entlast) currobj))
(setq coords (list 
(list 640.5625 -28.4663) 
(list 714.585 -28.9163) 
(list 714.585 -28.7393) 
(list 640.5625 -28.3893)))
(apply 'command (append '("pline") coords '("c")))
(setq currobj (ssadd (entlast) currobj))
(setq coords (list 
(list 640.5625 -28.2463) 
(list 714.585 -28.5963) 
(list 714.585 -28.4193) 
(list 640.5625 -28.1693)))
(apply 'command (append '("pline") coords '("c")))
(setq currobj (ssadd (entlast) currobj))
(setq coords (list 
(list 640.5625 -28.0263) 
(list 714.585 -28.2763) 
(list 714.585 -28.0993) 
(list 640.5625 -27.9493)))
(apply 'command (append '("pline") coords '("c")))
(setq currobj (ssadd (entlast) currobj))
(setq coords (list 
(list 640.5625 -27.8063) 
(list 714.585 -27.9563) 
(list 714.585 -27.7793) 
(list 640.5625 -27.7293)))
(apply 'command (append '("pline") coords '("c")))
(setq currobj (ssadd (entlast) currobj))
(setq coords (list 
(list 640.5625 -27.5863) 
(list 714.585 -27.6363) 
(list 714.585 -27.4593) 
(list 640.5625 -27.5093)))
(apply 'command (append '("pline") coords '("c")))
(setq currobj (ssadd (entlast) currobj))
(setq coords (list 
(list 640.5625 -27.3663) 
(list 714.585 -27.3163) 
(list 714.585 -27.1393) 
(list 640.5625 -27.2893)))
(apply 'command (append '("pline") coords '("c")))
(setq currobj (ssadd (entlast) currobj))
(setq coords (list 
(list 640.5625 -27.1463) 
(list 714.585 -26.9963) 
(list 714.585 -26.8193) 
(list 640.5625 -27.0693)))
(apply 'command (append '("pline") coords '("c")))
(setq currobj (ssadd (entlast) currobj))
(setq coords (list 
(list 640.5625 -26.9263) 
(list 714.585 -26.6763) 
(list 714.585 -26.4993) 
(list 640.5625 -26.8493)))
(apply 'command (append '("pline") coords '("c")))
(setq currobj (ssadd (entlast) currobj))
(setq coords (list 
(list 640.5625 -26.7063) 
(list 714.585 -26.3563) 
(list 714.585 -26.1793) 
(list 640.5625 -26.6293)))
(apply 'command (append '("pline") coords '("c")))
(setq currobj (ssadd (entlast) currobj))
(setq coords (list 
(list 640.5625 -26.4863) 
(list 714.585 -26.0363) 
(list 714.585 -25.8593) 
(list 640.5625 -26.4093)))
(apply 'command (append '("pline") coords '("c")))
(setq currobj (ssadd (entlast) currobj))
(setq coords (list 
(list 640.5625 -26.2663) 
(list 714.585 -25.7163) 
(list 714.585 -25.5393) 
(list 640.5625 -26.1893)))
(apply 'command (append '("pline") coords '("c")))
(setq currobj (ssadd (entlast) currobj))
(setq coords (list 
(list 640.5625 -26.0463) 
(list 714.585 -25.3963) 
(list 714.585 -25.2193) 
(list 640.5625 -25.9693)))
(apply 'command (append '("pline") coords '("c")))
(setq currobj (ssadd (entlast) currobj))
(setq coords (list 
(list 639.4375 -25.9693) 
(list 565.415 -25.2193) 
(list 565.415 -25.3963) 
(list 639.4375 -26.0463)))
(apply 'command (append '("pline") coords '("c")))
(setq currobj (ssadd (entlast) currobj))
(setq coords (list 
(list 639.4375 -26.1893) 
(list 565.415 -25.5393) 
(list 565.415 -25.7163) 
(list 639.4375 -26.2663)))
(apply 'command (append '("pline") coords '("c")))
(setq currobj (ssadd (entlast) currobj))
(setq coords (list 
(list 639.4375 -26.4093) 
(list 565.415 -25.8593) 
(list 565.415 -26.0363) 
(list 639.4375 -26.4863)))
(apply 'command (append '("pline") coords '("c")))
(setq currobj (ssadd (entlast) currobj))
(setq coords (list 
(list 639.4375 -26.6293) 
(list 565.415 -26.1793) 
(list 565.415 -26.3563) 
(list 639.4375 -26.7063)))
(apply 'command (append '("pline") coords '("c")))
(setq currobj (ssadd (entlast) currobj))
(setq coords (list 
(list 639.4375 -26.8493) 
(list 565.415 -26.4993) 
(list 565.415 -26.6763) 
(list 639.4375 -26.9263)))
(apply 'command (append '("pline") coords '("c")))
(setq currobj (ssadd (entlast) currobj))
(setq coords (list 
(list 639.4375 -27.0693) 
(list 565.415 -26.8193) 
(list 565.415 -26.9963) 
(list 639.4375 -27.1463)))
(apply 'command (append '("pline") coords '("c")))
(setq currobj (ssadd (entlast) currobj))
(setq coords (list 
(list 639.4375 -27.2893) 
(list 565.415 -27.1393) 
(list 565.415 -27.3163) 
(list 639.4375 -27.3663)))
(apply 'command (append '("pline") coords '("c")))
(setq currobj (ssadd (entlast) currobj))
(setq coords (list 
(list 639.4375 -27.5093) 
(list 565.415 -27.4593) 
(list 565.415 -27.6363) 
(list 639.4375 -27.5863)))
(apply 'command (append '("pline") coords '("c")))
(setq currobj (ssadd (entlast) currobj))
(setq coords (list 
(list 639.4375 -27.7293) 
(list 565.415 -27.7793) 
(list 565.415 -27.9563) 
(list 639.4375 -27.8063)))
(apply 'command (append '("pline") coords '("c")))
(setq currobj (ssadd (entlast) currobj))
(setq coords (list 
(list 639.4375 -27.9493) 
(list 565.415 -28.0993) 
(list 565.415 -28.2763) 
(list 639.4375 -28.0263)))
(apply 'command (append '("pline") coords '("c")))
(setq currobj (ssadd (entlast) currobj))
(setq coords (list 
(list 639.4375 -28.1693) 
(list 565.415 -28.4193) 
(list 565.415 -28.5963) 
(list 639.4375 -28.2463)))
(apply 'command (append '("pline") coords '("c")))
(setq currobj (ssadd (entlast) currobj))
(setq coords (list 
(list 639.4375 -28.3893) 
(list 565.415 -28.7393) 
(list 565.415 -28.9163) 
(list 639.4375 -28.4663)))
(apply 'command (append '("pline") coords '("c")))
(setq currobj (ssadd (entlast) currobj))
(setq coords (list 
(list 639.4375 -28.6093) 
(list 565.415 -29.0593) 
(list 565.415 -29.2363) 
(list 639.4375 -28.6863)))
(apply 'command (append '("pline") coords '("c")))
(setq currobj (ssadd (entlast) currobj))
(setq coords (list 
(list 639.4375 -28.8293) 
(list 565.415 -29.3793) 
(list 565.415 -29.5563) 
(list 639.4375 -28.9063)))
(apply 'command (append '("pline") coords '("c")))
(setq currobj (ssadd (entlast) currobj))
(setq coords (list 
(list 639.4375 -29.0493) 
(list 565.415 -29.6993) 
(list 565.415 -29.8763) 
(list 639.4375 -29.1263)))
(apply 'command (append '("pline") coords '("c")))
(setq currobj (ssadd (entlast) currobj))
(command "_layer" "set" "nitride" "")
(command "_layer" "set" "text" "")
(command "_circle" "639.0625,-40.2693" "0.075")
(command "_circle" "639.0625,-39.9693" "0.075")
(command "_circle" "639.0625,-39.6693" "0.075")
(command "_circle" "639.0625,-39.3693" "0.075")
(command "_circle" "639.0625,-39.0693" "0.075")
(command "_circle" "638.7625,-40.2693" "0.075")
(command "_circle" "638.7625,-39.9693" "0.075")
(command "_circle" "638.7625,-39.6693" "0.075")
(command "_circle" "638.7625,-39.3693" "0.075")
(command "_circle" "638.7625,-39.0693" "0.075")
(command "_circle" "638.4625,-40.2693" "0.075")
(command "_circle" "638.4625,-39.9693" "0.075")
(command "_circle" "638.4625,-39.6693" "0.075")
(command "_circle" "638.4625,-39.3693" "0.075")
(command "_circle" "638.4625,-39.0693" "0.075")
(command "_circle" "638.1625,-40.2693" "0.075")
(command "_circle" "638.1625,-39.9693" "0.075")
(command "_circle" "638.1625,-39.6693" "0.075")
(command "_circle" "638.1625,-39.3693" "0.075")
(command "_circle" "638.1625,-39.0693" "0.075")
(command "_circle" "637.8625,-40.2693" "0.075")
(command "_circle" "637.8625,-39.9693" "0.075")
(command "_circle" "637.8625,-39.6693" "0.075")
(command "_circle" "637.8625,-39.3693" "0.075")
(command "_circle" "637.8625,-39.0693" "0.075")
(command "_layer" "set" "nitride" "")
(setq coords (list 
(list 640.2625 -14.8263) 
(list 640.2625 100.8184) 
(list 639.7375 100.8184) 
(list 639.7375 -14.8263)))
(apply 'command (append '("pline") coords '("c")))
(setq currobj (ssadd (entlast) currobj))
(command "_layer" "set" "prebias" "")
(command "_rectangle" "639.7375,-14.8263" "640.2625,100.8184")
(setq currobj (ssadd (entlast) currobj))
(command "_layer" "set" "nitride" "")
(setq coords (list 
(list 640.2625 100.8184) 
(list 640.5625 110.8184) 
(list 640.5625 110.8184) 
(list 640.5625 111.8184) 
(list 714.585 111.0684) 
(list 714.585 116.0114) 
(list 640.5625 115.2614) 
(list 640.5625 116.2614) 
(list 640.5625 116.2614) 
(list 640.2625 126.2614) 
(list 639.7375 126.2614) 
(list 639.4375 116.2614) 
(list 639.4375 116.2614) 
(list 639.4375 115.2614) 
(list 565.415 116.0114) 
(list 565.415 111.0684) 
(list 639.4375 111.8184) 
(list 639.4375 110.8184) 
(list 639.4375 110.8184) 
(list 639.7375 100.8184)))
(apply 'command (append '("pline") coords '("c")))
(setq currobj (ssadd (entlast) currobj))
(command "_layer" "set" "prebias" "")
(setq coords (list 
(list 639.4375 100.8184) 
(list 639.4375 111.8184) 
(list 565.415 111.0684) 
(list 565.415 116.0114) 
(list 639.4375 115.2614) 
(list 639.4375 126.2614) 
(list 640.5625 126.2614) 
(list 640.5625 115.2614) 
(list 714.585 116.0114) 
(list 714.585 111.0684) 
(list 640.5625 111.8184) 
(list 640.5625 100.8184)))
(apply 'command (append '("pline") coords '("c")))
(setq currobj (ssadd (entlast) currobj))
(command "_layer" "set" "nitride" "")
(command "_layer" "set" "fda1" "")
(setq coords (list 
(list 640.5625 111.9614) 
(list 714.585 111.2114) 
(list 714.585 111.3884) 
(list 640.5625 112.0384)))
(apply 'command (append '("pline") coords '("c")))
(setq currobj (ssadd (entlast) currobj))
(setq coords (list 
(list 640.5625 112.1814) 
(list 714.585 111.5314) 
(list 714.585 111.7084) 
(list 640.5625 112.2584)))
(apply 'command (append '("pline") coords '("c")))
(setq currobj (ssadd (entlast) currobj))
(setq coords (list 
(list 640.5625 112.4014) 
(list 714.585 111.8514) 
(list 714.585 112.0284) 
(list 640.5625 112.4784)))
(apply 'command (append '("pline") coords '("c")))
(setq currobj (ssadd (entlast) currobj))
(setq coords (list 
(list 640.5625 112.6214) 
(list 714.585 112.1714) 
(list 714.585 112.3484) 
(list 640.5625 112.6984)))
(apply 'command (append '("pline") coords '("c")))
(setq currobj (ssadd (entlast) currobj))
(setq coords (list 
(list 640.5625 112.8414) 
(list 714.585 112.4914) 
(list 714.585 112.6684) 
(list 640.5625 112.9184)))
(apply 'command (append '("pline") coords '("c")))
(setq currobj (ssadd (entlast) currobj))
(setq coords (list 
(list 640.5625 113.0614) 
(list 714.585 112.8114) 
(list 714.585 112.9884) 
(list 640.5625 113.1384)))
(apply 'command (append '("pline") coords '("c")))
(setq currobj (ssadd (entlast) currobj))
(setq coords (list 
(list 640.5625 113.2814) 
(list 714.585 113.1314) 
(list 714.585 113.3084) 
(list 640.5625 113.3584)))
(apply 'command (append '("pline") coords '("c")))
(setq currobj (ssadd (entlast) currobj))
(setq coords (list 
(list 640.5625 113.5014) 
(list 714.585 113.4514) 
(list 714.585 113.6284) 
(list 640.5625 113.5784)))
(apply 'command (append '("pline") coords '("c")))
(setq currobj (ssadd (entlast) currobj))
(setq coords (list 
(list 640.5625 113.7214) 
(list 714.585 113.7714) 
(list 714.585 113.9484) 
(list 640.5625 113.7984)))
(apply 'command (append '("pline") coords '("c")))
(setq currobj (ssadd (entlast) currobj))
(setq coords (list 
(list 640.5625 113.9414) 
(list 714.585 114.0914) 
(list 714.585 114.2684) 
(list 640.5625 114.0184)))
(apply 'command (append '("pline") coords '("c")))
(setq currobj (ssadd (entlast) currobj))
(setq coords (list 
(list 640.5625 114.1614) 
(list 714.585 114.4114) 
(list 714.585 114.5884) 
(list 640.5625 114.2384)))
(apply 'command (append '("pline") coords '("c")))
(setq currobj (ssadd (entlast) currobj))
(setq coords (list 
(list 640.5625 114.3814) 
(list 714.585 114.7314) 
(list 714.585 114.9084) 
(list 640.5625 114.4584)))
(apply 'command (append '("pline") coords '("c")))
(setq currobj (ssadd (entlast) currobj))
(setq coords (list 
(list 640.5625 114.6014) 
(list 714.585 115.0514) 
(list 714.585 115.2284) 
(list 640.5625 114.6784)))
(apply 'command (append '("pline") coords '("c")))
(setq currobj (ssadd (entlast) currobj))
(setq coords (list 
(list 640.5625 114.8214) 
(list 714.585 115.3714) 
(list 714.585 115.5484) 
(list 640.5625 114.8984)))
(apply 'command (append '("pline") coords '("c")))
(setq currobj (ssadd (entlast) currobj))
(setq coords (list 
(list 640.5625 115.0414) 
(list 714.585 115.6914) 
(list 714.585 115.8684) 
(list 640.5625 115.1184)))
(apply 'command (append '("pline") coords '("c")))
(setq currobj (ssadd (entlast) currobj))
(setq coords (list 
(list 639.4375 115.1184) 
(list 565.415 115.8684) 
(list 565.415 115.6914) 
(list 639.4375 115.0414)))
(apply 'command (append '("pline") coords '("c")))
(setq currobj (ssadd (entlast) currobj))
(setq coords (list 
(list 639.4375 114.8984) 
(list 565.415 115.5484) 
(list 565.415 115.3714) 
(list 639.4375 114.8214)))
(apply 'command (append '("pline") coords '("c")))
(setq currobj (ssadd (entlast) currobj))
(setq coords (list 
(list 639.4375 114.6784) 
(list 565.415 115.2284) 
(list 565.415 115.0514) 
(list 639.4375 114.6014)))
(apply 'command (append '("pline") coords '("c")))
(setq currobj (ssadd (entlast) currobj))
(setq coords (list 
(list 639.4375 114.4584) 
(list 565.415 114.9084) 
(list 565.415 114.7314) 
(list 639.4375 114.3814)))
(apply 'command (append '("pline") coords '("c")))
(setq currobj (ssadd (entlast) currobj))
(setq coords (list 
(list 639.4375 114.2384) 
(list 565.415 114.5884) 
(list 565.415 114.4114) 
(list 639.4375 114.1614)))
(apply 'command (append '("pline") coords '("c")))
(setq currobj (ssadd (entlast) currobj))
(setq coords (list 
(list 639.4375 114.0184) 
(list 565.415 114.2684) 
(list 565.415 114.0914) 
(list 639.4375 113.9414)))
(apply 'command (append '("pline") coords '("c")))
(setq currobj (ssadd (entlast) currobj))
(setq coords (list 
(list 639.4375 113.7984) 
(list 565.415 113.9484) 
(list 565.415 113.7714) 
(list 639.4375 113.7214)))
(apply 'command (append '("pline") coords '("c")))
(setq currobj (ssadd (entlast) currobj))
(setq coords (list 
(list 639.4375 113.5784) 
(list 565.415 113.6284) 
(list 565.415 113.4514) 
(list 639.4375 113.5014)))
(apply 'command (append '("pline") coords '("c")))
(setq currobj (ssadd (entlast) currobj))
(setq coords (list 
(list 639.4375 113.3584) 
(list 565.415 113.3084) 
(list 565.415 113.1314) 
(list 639.4375 113.2814)))
(apply 'command (append '("pline") coords '("c")))
(setq currobj (ssadd (entlast) currobj))
(setq coords (list 
(list 639.4375 113.1384) 
(list 565.415 112.9884) 
(list 565.415 112.8114) 
(list 639.4375 113.0614)))
(apply 'command (append '("pline") coords '("c")))
(setq currobj (ssadd (entlast) currobj))
(setq coords (list 
(list 639.4375 112.9184) 
(list 565.415 112.6684) 
(list 565.415 112.4914) 
(list 639.4375 112.8414)))
(apply 'command (append '("pline") coords '("c")))
(setq currobj (ssadd (entlast) currobj))
(setq coords (list 
(list 639.4375 112.6984) 
(list 565.415 112.3484) 
(list 565.415 112.1714) 
(list 639.4375 112.6214)))
(apply 'command (append '("pline") coords '("c")))
(setq currobj (ssadd (entlast) currobj))
(setq coords (list 
(list 639.4375 112.4784) 
(list 565.415 112.0284) 
(list 565.415 111.8514) 
(list 639.4375 112.4014)))
(apply 'command (append '("pline") coords '("c")))
(setq currobj (ssadd (entlast) currobj))
(setq coords (list 
(list 639.4375 112.2584) 
(list 565.415 111.7084) 
(list 565.415 111.5314) 
(list 639.4375 112.1814)))
(apply 'command (append '("pline") coords '("c")))
(setq currobj (ssadd (entlast) currobj))
(setq coords (list 
(list 639.4375 112.0384) 
(list 565.415 111.3884) 
(list 565.415 111.2114) 
(list 639.4375 111.9614)))
(apply 'command (append '("pline") coords '("c")))
(setq currobj (ssadd (entlast) currobj))
(command "_layer" "set" "nitride" "")
(command "_layer" "set" "text" "")
(command "_circle" "639.0625,100.8184" "0.075")
(command "_circle" "639.0625,101.1184" "0.075")
(command "_circle" "639.0625,101.4184" "0.075")
(command "_circle" "639.0625,101.7184" "0.075")
(command "_circle" "639.0625,102.0184" "0.075")
(command "_circle" "638.7625,100.8184" "0.075")
(command "_circle" "638.7625,101.1184" "0.075")
(command "_circle" "638.7625,101.4184" "0.075")
(command "_circle" "638.7625,101.7184" "0.075")
(command "_circle" "638.7625,102.0184" "0.075")
(command "_circle" "638.4625,100.8184" "0.075")
(command "_circle" "638.4625,101.1184" "0.075")
(command "_circle" "638.4625,101.4184" "0.075")
(command "_circle" "638.4625,101.7184" "0.075")
(command "_circle" "638.4625,102.0184" "0.075")
(command "_circle" "638.1625,100.8184" "0.075")
(command "_circle" "638.1625,101.1184" "0.075")
(command "_circle" "638.1625,101.4184" "0.075")
(command "_circle" "638.1625,101.7184" "0.075")
(command "_circle" "638.1625,102.0184" "0.075")
(command "_circle" "637.8625,100.8184" "0.075")
(command "_circle" "637.8625,101.1184" "0.075")
(command "_circle" "637.8625,101.4184" "0.075")
(command "_circle" "637.8625,101.7184" "0.075")
(command "_circle" "637.8625,102.0184" "0.075")
(command "_layer" "set" "nitride" "")
(setq coords (list 
(list 640.2625 126.2614) 
(list 640.2625 241.9061) 
(list 639.7375 241.9061) 
(list 639.7375 126.2614)))
(apply 'command (append '("pline") coords '("c")))
(setq currobj (ssadd (entlast) currobj))
(command "_layer" "set" "prebias" "")
(command "_rectangle" "639.7375,126.2614" "640.2625,241.9061")
(setq currobj (ssadd (entlast) currobj))
(command "_layer" "set" "nitride" "")
(setq coords (list 
(list 640.2625 241.9061) 
(list 640.5625 251.9061) 
(list 640.5625 251.9061) 
(list 640.5625 252.9061) 
(list 714.585 252.1561) 
(list 714.585 257.0991) 
(list 640.5625 256.3491) 
(list 640.5625 257.3491) 
(list 640.5625 257.3491) 
(list 640.2625 267.3491) 
(list 639.7375 267.3491) 
(list 639.4375 257.3491) 
(list 639.4375 257.3491) 
(list 639.4375 256.3491) 
(list 565.415 257.0991) 
(list 565.415 252.1561) 
(list 639.4375 252.9061) 
(list 639.4375 251.9061) 
(list 639.4375 251.9061) 
(list 639.7375 241.9061)))
(apply 'command (append '("pline") coords '("c")))
(setq currobj (ssadd (entlast) currobj))
(command "_layer" "set" "prebias" "")
(setq coords (list 
(list 639.4375 241.9061) 
(list 639.4375 252.9061) 
(list 565.415 252.1561) 
(list 565.415 257.0991) 
(list 639.4375 256.3491) 
(list 639.4375 267.3491) 
(list 640.5625 267.3491) 
(list 640.5625 256.3491) 
(list 714.585 257.0991) 
(list 714.585 252.1561) 
(list 640.5625 252.9061) 
(list 640.5625 241.9061)))
(apply 'command (append '("pline") coords '("c")))
(setq currobj (ssadd (entlast) currobj))
(command "_layer" "set" "nitride" "")
(command "_layer" "set" "fda1" "")
(setq coords (list 
(list 640.5625 253.0491) 
(list 714.585 252.2991) 
(list 714.585 252.4761) 
(list 640.5625 253.1261)))
(apply 'command (append '("pline") coords '("c")))
(setq currobj (ssadd (entlast) currobj))
(setq coords (list 
(list 640.5625 253.2691) 
(list 714.585 252.6191) 
(list 714.585 252.7961) 
(list 640.5625 253.3461)))
(apply 'command (append '("pline") coords '("c")))
(setq currobj (ssadd (entlast) currobj))
(setq coords (list 
(list 640.5625 253.4891) 
(list 714.585 252.9391) 
(list 714.585 253.1161) 
(list 640.5625 253.5661)))
(apply 'command (append '("pline") coords '("c")))
(setq currobj (ssadd (entlast) currobj))
(setq coords (list 
(list 640.5625 253.7091) 
(list 714.585 253.2591) 
(list 714.585 253.4361) 
(list 640.5625 253.7861)))
(apply 'command (append '("pline") coords '("c")))
(setq currobj (ssadd (entlast) currobj))
(setq coords (list 
(list 640.5625 253.9291) 
(list 714.585 253.5791) 
(list 714.585 253.7561) 
(list 640.5625 254.0061)))
(apply 'command (append '("pline") coords '("c")))
(setq currobj (ssadd (entlast) currobj))
(setq coords (list 
(list 640.5625 254.1491) 
(list 714.585 253.8991) 
(list 714.585 254.0761) 
(list 640.5625 254.2261)))
(apply 'command (append '("pline") coords '("c")))
(setq currobj (ssadd (entlast) currobj))
(setq coords (list 
(list 640.5625 254.3691) 
(list 714.585 254.2191) 
(list 714.585 254.3961) 
(list 640.5625 254.4461)))
(apply 'command (append '("pline") coords '("c")))
(setq currobj (ssadd (entlast) currobj))
(setq coords (list 
(list 640.5625 254.5891) 
(list 714.585 254.5391) 
(list 714.585 254.7161) 
(list 640.5625 254.6661)))
(apply 'command (append '("pline") coords '("c")))
(setq currobj (ssadd (entlast) currobj))
(setq coords (list 
(list 640.5625 254.8091) 
(list 714.585 254.8591) 
(list 714.585 255.0361) 
(list 640.5625 254.8861)))
(apply 'command (append '("pline") coords '("c")))
(setq currobj (ssadd (entlast) currobj))
(setq coords (list 
(list 640.5625 255.0291) 
(list 714.585 255.1791) 
(list 714.585 255.3561) 
(list 640.5625 255.1061)))
(apply 'command (append '("pline") coords '("c")))
(setq currobj (ssadd (entlast) currobj))
(setq coords (list 
(list 640.5625 255.2491) 
(list 714.585 255.4991) 
(list 714.585 255.6761) 
(list 640.5625 255.3261)))
(apply 'command (append '("pline") coords '("c")))
(setq currobj (ssadd (entlast) currobj))
(setq coords (list 
(list 640.5625 255.4691) 
(list 714.585 255.8191) 
(list 714.585 255.9961) 
(list 640.5625 255.5461)))
(apply 'command (append '("pline") coords '("c")))
(setq currobj (ssadd (entlast) currobj))
(setq coords (list 
(list 640.5625 255.6891) 
(list 714.585 256.1391) 
(list 714.585 256.3161) 
(list 640.5625 255.7661)))
(apply 'command (append '("pline") coords '("c")))
(setq currobj (ssadd (entlast) currobj))
(setq coords (list 
(list 640.5625 255.9091) 
(list 714.585 256.4591) 
(list 714.585 256.6361) 
(list 640.5625 255.9861)))
(apply 'command (append '("pline") coords '("c")))
(setq currobj (ssadd (entlast) currobj))
(setq coords (list 
(list 640.5625 256.1291) 
(list 714.585 256.7791) 
(list 714.585 256.9561) 
(list 640.5625 256.2061)))
(apply 'command (append '("pline") coords '("c")))
(setq currobj (ssadd (entlast) currobj))
(setq coords (list 
(list 639.4375 256.2061) 
(list 565.415 256.9561) 
(list 565.415 256.7791) 
(list 639.4375 256.1291)))
(apply 'command (append '("pline") coords '("c")))
(setq currobj (ssadd (entlast) currobj))
(setq coords (list 
(list 639.4375 255.9861) 
(list 565.415 256.6361) 
(list 565.415 256.4591) 
(list 639.4375 255.9091)))
(apply 'command (append '("pline") coords '("c")))
(setq currobj (ssadd (entlast) currobj))
(setq coords (list 
(list 639.4375 255.7661) 
(list 565.415 256.3161) 
(list 565.415 256.1391) 
(list 639.4375 255.6891)))
(apply 'command (append '("pline") coords '("c")))
(setq currobj (ssadd (entlast) currobj))
(setq coords (list 
(list 639.4375 255.5461) 
(list 565.415 255.9961) 
(list 565.415 255.8191) 
(list 639.4375 255.4691)))
(apply 'command (append '("pline") coords '("c")))
(setq currobj (ssadd (entlast) currobj))
(setq coords (list 
(list 639.4375 255.3261) 
(list 565.415 255.6761) 
(list 565.415 255.4991) 
(list 639.4375 255.2491)))
(apply 'command (append '("pline") coords '("c")))
(setq currobj (ssadd (entlast) currobj))
(setq coords (list 
(list 639.4375 255.1061) 
(list 565.415 255.3561) 
(list 565.415 255.1791) 
(list 639.4375 255.0291)))
(apply 'command (append '("pline") coords '("c")))
(setq currobj (ssadd (entlast) currobj))
(setq coords (list 
(list 639.4375 254.8861) 
(list 565.415 255.0361) 
(list 565.415 254.8591) 
(list 639.4375 254.8091)))
(apply 'command (append '("pline") coords '("c")))
(setq currobj (ssadd (entlast) currobj))
(setq coords (list 
(list 639.4375 254.6661) 
(list 565.415 254.7161) 
(list 565.415 254.5391) 
(list 639.4375 254.5891)))
(apply 'command (append '("pline") coords '("c")))
(setq currobj (ssadd (entlast) currobj))
(setq coords (list 
(list 639.4375 254.4461) 
(list 565.415 254.3961) 
(list 565.415 254.2191) 
(list 639.4375 254.3691)))
(apply 'command (append '("pline") coords '("c")))
(setq currobj (ssadd (entlast) currobj))
(setq coords (list 
(list 639.4375 254.2261) 
(list 565.415 254.0761) 
(list 565.415 253.8991) 
(list 639.4375 254.1491)))
(apply 'command (append '("pline") coords '("c")))
(setq currobj (ssadd (entlast) currobj))
(setq coords (list 
(list 639.4375 254.0061) 
(list 565.415 253.7561) 
(list 565.415 253.5791) 
(list 639.4375 253.9291)))
(apply 'command (append '("pline") coords '("c")))
(setq currobj (ssadd (entlast) currobj))
(setq coords (list 
(list 639.4375 253.7861) 
(list 565.415 253.4361) 
(list 565.415 253.2591) 
(list 639.4375 253.7091)))
(apply 'command (append '("pline") coords '("c")))
(setq currobj (ssadd (entlast) currobj))
(setq coords (list 
(list 639.4375 253.5661) 
(list 565.415 253.1161) 
(list 565.415 252.9391) 
(list 639.4375 253.4891)))
(apply 'command (append '("pline") coords '("c")))
(setq currobj (ssadd (entlast) currobj))
(setq coords (list 
(list 639.4375 253.3461) 
(list 565.415 252.7961) 
(list 565.415 252.6191) 
(list 639.4375 253.2691)))
(apply 'command (append '("pline") coords '("c")))
(setq currobj (ssadd (entlast) currobj))
(setq coords (list 
(list 639.4375 253.1261) 
(list 565.415 252.4761) 
(list 565.415 252.2991) 
(list 639.4375 253.0491)))
(apply 'command (append '("pline") coords '("c")))
(setq currobj (ssadd (entlast) currobj))
(command "_layer" "set" "nitride" "")
(command "_layer" "set" "text" "")
(command "_circle" "639.0625,241.9061" "0.075")
(command "_circle" "639.0625,242.2061" "0.075")
(command "_circle" "639.0625,242.5061" "0.075")
(command "_circle" "639.0625,242.8061" "0.075")
(command "_circle" "639.0625,243.1061" "0.075")
(command "_circle" "638.7625,241.9061" "0.075")
(command "_circle" "638.7625,242.2061" "0.075")
(command "_circle" "638.7625,242.5061" "0.075")
(command "_circle" "638.7625,242.8061" "0.075")
(command "_circle" "638.7625,243.1061" "0.075")
(command "_circle" "638.4625,241.9061" "0.075")
(command "_circle" "638.4625,242.2061" "0.075")
(command "_circle" "638.4625,242.5061" "0.075")
(command "_circle" "638.4625,242.8061" "0.075")
(command "_circle" "638.4625,243.1061" "0.075")
(command "_circle" "638.1625,241.9061" "0.075")
(command "_circle" "638.1625,242.2061" "0.075")
(command "_circle" "638.1625,242.5061" "0.075")
(command "_circle" "638.1625,242.8061" "0.075")
(command "_circle" "638.1625,243.1061" "0.075")
(command "_circle" "637.8625,241.9061" "0.075")
(command "_circle" "637.8625,242.2061" "0.075")
(command "_circle" "637.8625,242.5061" "0.075")
(command "_circle" "637.8625,242.8061" "0.075")
(command "_circle" "637.8625,243.1061" "0.075")
(command "_layer" "set" "nitride" "")
(setq coords (list 
(list 640.2625 267.3491) 
(list 640.2625 382.9939) 
(list 639.7375 382.9939) 
(list 639.7375 267.3491)))
(apply 'command (append '("pline") coords '("c")))
(setq currobj (ssadd (entlast) currobj))
(command "_layer" "set" "prebias" "")
(command "_rectangle" "639.7375,267.3491" "640.2625,382.9939")
(setq currobj (ssadd (entlast) currobj))
(command "_layer" "set" "nitride" "")
(setq coords (list 
(list 640.2625 382.9939) 
(list 640.5625 392.9939) 
(list 640.5625 392.9939) 
(list 640.5625 393.9939) 
(list 714.585 393.2439) 
(list 714.585 398.1869) 
(list 640.5625 397.4369) 
(list 640.5625 398.4369) 
(list 640.5625 398.4369) 
(list 640.2625 408.4369) 
(list 639.7375 408.4369) 
(list 639.4375 398.4369) 
(list 639.4375 398.4369) 
(list 639.4375 397.4369) 
(list 565.415 398.1869) 
(list 565.415 393.2439) 
(list 639.4375 393.9939) 
(list 639.4375 392.9939) 
(list 639.4375 392.9939) 
(list 639.7375 382.9939)))
(apply 'command (append '("pline") coords '("c")))
(setq currobj (ssadd (entlast) currobj))
(command "_layer" "set" "prebias" "")
(setq coords (list 
(list 639.4375 382.9939) 
(list 639.4375 393.9939) 
(list 565.415 393.2439) 
(list 565.415 398.1869) 
(list 639.4375 397.4369) 
(list 639.4375 408.4369) 
(list 640.5625 408.4369) 
(list 640.5625 397.4369) 
(list 714.585 398.1869) 
(list 714.585 393.2439) 
(list 640.5625 393.9939) 
(list 640.5625 382.9939)))
(apply 'command (append '("pline") coords '("c")))
(setq currobj (ssadd (entlast) currobj))
(command "_layer" "set" "nitride" "")
(command "_layer" "set" "fda1" "")
(setq coords (list 
(list 640.5625 394.1369) 
(list 714.585 393.3869) 
(list 714.585 393.5639) 
(list 640.5625 394.2139)))
(apply 'command (append '("pline") coords '("c")))
(setq currobj (ssadd (entlast) currobj))
(setq coords (list 
(list 640.5625 394.3569) 
(list 714.585 393.7069) 
(list 714.585 393.8839) 
(list 640.5625 394.4339)))
(apply 'command (append '("pline") coords '("c")))
(setq currobj (ssadd (entlast) currobj))
(setq coords (list 
(list 640.5625 394.5769) 
(list 714.585 394.0269) 
(list 714.585 394.2039) 
(list 640.5625 394.6539)))
(apply 'command (append '("pline") coords '("c")))
(setq currobj (ssadd (entlast) currobj))
(setq coords (list 
(list 640.5625 394.7969) 
(list 714.585 394.3469) 
(list 714.585 394.5239) 
(list 640.5625 394.8739)))
(apply 'command (append '("pline") coords '("c")))
(setq currobj (ssadd (entlast) currobj))
(setq coords (list 
(list 640.5625 395.0169) 
(list 714.585 394.6669) 
(list 714.585 394.8439) 
(list 640.5625 395.0939)))
(apply 'command (append '("pline") coords '("c")))
(setq currobj (ssadd (entlast) currobj))
(setq coords (list 
(list 640.5625 395.2369) 
(list 714.585 394.9869) 
(list 714.585 395.1639) 
(list 640.5625 395.3139)))
(apply 'command (append '("pline") coords '("c")))
(setq currobj (ssadd (entlast) currobj))
(setq coords (list 
(list 640.5625 395.4569) 
(list 714.585 395.3069) 
(list 714.585 395.4839) 
(list 640.5625 395.5339)))
(apply 'command (append '("pline") coords '("c")))
(setq currobj (ssadd (entlast) currobj))
(setq coords (list 
(list 640.5625 395.6769) 
(list 714.585 395.6269) 
(list 714.585 395.8039) 
(list 640.5625 395.7539)))
(apply 'command (append '("pline") coords '("c")))
(setq currobj (ssadd (entlast) currobj))
(setq coords (list 
(list 640.5625 395.8969) 
(list 714.585 395.9469) 
(list 714.585 396.1239) 
(list 640.5625 395.9739)))
(apply 'command (append '("pline") coords '("c")))
(setq currobj (ssadd (entlast) currobj))
(setq coords (list 
(list 640.5625 396.1169) 
(list 714.585 396.2669) 
(list 714.585 396.4439) 
(list 640.5625 396.1939)))
(apply 'command (append '("pline") coords '("c")))
(setq currobj (ssadd (entlast) currobj))
(setq coords (list 
(list 640.5625 396.3369) 
(list 714.585 396.5869) 
(list 714.585 396.7639) 
(list 640.5625 396.4139)))
(apply 'command (append '("pline") coords '("c")))
(setq currobj (ssadd (entlast) currobj))
(setq coords (list 
(list 640.5625 396.5569) 
(list 714.585 396.9069) 
(list 714.585 397.0839) 
(list 640.5625 396.6339)))
(apply 'command (append '("pline") coords '("c")))
(setq currobj (ssadd (entlast) currobj))
(setq coords (list 
(list 640.5625 396.7769) 
(list 714.585 397.2269) 
(list 714.585 397.4039) 
(list 640.5625 396.8539)))
(apply 'command (append '("pline") coords '("c")))
(setq currobj (ssadd (entlast) currobj))
(setq coords (list 
(list 640.5625 396.9969) 
(list 714.585 397.5469) 
(list 714.585 397.7239) 
(list 640.5625 397.0739)))
(apply 'command (append '("pline") coords '("c")))
(setq currobj (ssadd (entlast) currobj))
(setq coords (list 
(list 640.5625 397.2169) 
(list 714.585 397.8669) 
(list 714.585 398.0439) 
(list 640.5625 397.2939)))
(apply 'command (append '("pline") coords '("c")))
(setq currobj (ssadd (entlast) currobj))
(setq coords (list 
(list 639.4375 397.2939) 
(list 565.415 398.0439) 
(list 565.415 397.8669) 
(list 639.4375 397.2169)))
(apply 'command (append '("pline") coords '("c")))
(setq currobj (ssadd (entlast) currobj))
(setq coords (list 
(list 639.4375 397.0739) 
(list 565.415 397.7239) 
(list 565.415 397.5469) 
(list 639.4375 396.9969)))
(apply 'command (append '("pline") coords '("c")))
(setq currobj (ssadd (entlast) currobj))
(setq coords (list 
(list 639.4375 396.8539) 
(list 565.415 397.4039) 
(list 565.415 397.2269) 
(list 639.4375 396.7769)))
(apply 'command (append '("pline") coords '("c")))
(setq currobj (ssadd (entlast) currobj))
(setq coords (list 
(list 639.4375 396.6339) 
(list 565.415 397.0839) 
(list 565.415 396.9069) 
(list 639.4375 396.5569)))
(apply 'command (append '("pline") coords '("c")))
(setq currobj (ssadd (entlast) currobj))
(setq coords (list 
(list 639.4375 396.4139) 
(list 565.415 396.7639) 
(list 565.415 396.5869) 
(list 639.4375 396.3369)))
(apply 'command (append '("pline") coords '("c")))
(setq currobj (ssadd (entlast) currobj))
(setq coords (list 
(list 639.4375 396.1939) 
(list 565.415 396.4439) 
(list 565.415 396.2669) 
(list 639.4375 396.1169)))
(apply 'command (append '("pline") coords '("c")))
(setq currobj (ssadd (entlast) currobj))
(setq coords (list 
(list 639.4375 395.9739) 
(list 565.415 396.1239) 
(list 565.415 395.9469) 
(list 639.4375 395.8969)))
(apply 'command (append '("pline") coords '("c")))
(setq currobj (ssadd (entlast) currobj))
(setq coords (list 
(list 639.4375 395.7539) 
(list 565.415 395.8039) 
(list 565.415 395.6269) 
(list 639.4375 395.6769)))
(apply 'command (append '("pline") coords '("c")))
(setq currobj (ssadd (entlast) currobj))
(setq coords (list 
(list 639.4375 395.5339) 
(list 565.415 395.4839) 
(list 565.415 395.3069) 
(list 639.4375 395.4569)))
(apply 'command (append '("pline") coords '("c")))
(setq currobj (ssadd (entlast) currobj))
(setq coords (list 
(list 639.4375 395.3139) 
(list 565.415 395.1639) 
(list 565.415 394.9869) 
(list 639.4375 395.2369)))
(apply 'command (append '("pline") coords '("c")))
(setq currobj (ssadd (entlast) currobj))
(setq coords (list 
(list 639.4375 395.0939) 
(list 565.415 394.8439) 
(list 565.415 394.6669) 
(list 639.4375 395.0169)))
(apply 'command (append '("pline") coords '("c")))
(setq currobj (ssadd (entlast) currobj))
(setq coords (list 
(list 639.4375 394.8739) 
(list 565.415 394.5239) 
(list 565.415 394.3469) 
(list 639.4375 394.7969)))
(apply 'command (append '("pline") coords '("c")))
(setq currobj (ssadd (entlast) currobj))
(setq coords (list 
(list 639.4375 394.6539) 
(list 565.415 394.2039) 
(list 565.415 394.0269) 
(list 639.4375 394.5769)))
(apply 'command (append '("pline") coords '("c")))
(setq currobj (ssadd (entlast) currobj))
(setq coords (list 
(list 639.4375 394.4339) 
(list 565.415 393.8839) 
(list 565.415 393.7069) 
(list 639.4375 394.3569)))
(apply 'command (append '("pline") coords '("c")))
(setq currobj (ssadd (entlast) currobj))
(setq coords (list 
(list 639.4375 394.2139) 
(list 565.415 393.5639) 
(list 565.415 393.3869) 
(list 639.4375 394.1369)))
(apply 'command (append '("pline") coords '("c")))
(setq currobj (ssadd (entlast) currobj))
(command "_layer" "set" "nitride" "")
(command "_layer" "set" "text" "")
(command "_circle" "639.0625,382.9939" "0.075")
(command "_circle" "639.0625,383.2939" "0.075")
(command "_circle" "639.0625,383.5939" "0.075")
(command "_circle" "639.0625,383.8939" "0.075")
(command "_circle" "639.0625,384.1939" "0.075")
(command "_circle" "638.7625,382.9939" "0.075")
(command "_circle" "638.7625,383.2939" "0.075")
(command "_circle" "638.7625,383.5939" "0.075")
(command "_circle" "638.7625,383.8939" "0.075")
(command "_circle" "638.7625,384.1939" "0.075")
(command "_circle" "638.4625,382.9939" "0.075")
(command "_circle" "638.4625,383.2939" "0.075")
(command "_circle" "638.4625,383.5939" "0.075")
(command "_circle" "638.4625,383.8939" "0.075")
(command "_circle" "638.4625,384.1939" "0.075")
(command "_circle" "638.1625,382.9939" "0.075")
(command "_circle" "638.1625,383.2939" "0.075")
(command "_circle" "638.1625,383.5939" "0.075")
(command "_circle" "638.1625,383.8939" "0.075")
(command "_circle" "638.1625,384.1939" "0.075")
(command "_circle" "637.8625,382.9939" "0.075")
(command "_circle" "637.8625,383.2939" "0.075")
(command "_circle" "637.8625,383.5939" "0.075")
(command "_circle" "637.8625,383.8939" "0.075")
(command "_circle" "637.8625,384.1939" "0.075")
(command "_layer" "set" "nitride" "")
(setq coords (list 
(list 640.2625 408.4369) 
(list 640.2625 524.0816) 
(list 639.7375 524.0816) 
(list 639.7375 408.4369)))
(apply 'command (append '("pline") coords '("c")))
(setq currobj (ssadd (entlast) currobj))
(command "_layer" "set" "prebias" "")
(command "_rectangle" "639.7375,408.4369" "640.2625,524.0816")
(setq currobj (ssadd (entlast) currobj))
(command "_layer" "set" "nitride" "")
(setq coords (list 
(list 640.2625 524.0816) 
(list 640.5625 534.0816) 
(list 640.5625 534.0816) 
(list 640.5625 535.0816) 
(list 714.585 534.3316) 
(list 714.585 539.2746) 
(list 640.5625 538.5246) 
(list 640.5625 539.5246) 
(list 640.5625 539.5246) 
(list 640.2625 549.5246) 
(list 639.7375 549.5246) 
(list 639.4375 539.5246) 
(list 639.4375 539.5246) 
(list 639.4375 538.5246) 
(list 565.415 539.2746) 
(list 565.415 534.3316) 
(list 639.4375 535.0816) 
(list 639.4375 534.0816) 
(list 639.4375 534.0816) 
(list 639.7375 524.0816)))
(apply 'command (append '("pline") coords '("c")))
(setq currobj (ssadd (entlast) currobj))
(command "_layer" "set" "prebias" "")
(setq coords (list 
(list 639.4375 524.0816) 
(list 639.4375 535.0816) 
(list 565.415 534.3316) 
(list 565.415 539.2746) 
(list 639.4375 538.5246) 
(list 639.4375 549.5246) 
(list 640.5625 549.5246) 
(list 640.5625 538.5246) 
(list 714.585 539.2746) 
(list 714.585 534.3316) 
(list 640.5625 535.0816) 
(list 640.5625 524.0816)))
(apply 'command (append '("pline") coords '("c")))
(setq currobj (ssadd (entlast) currobj))
(command "_layer" "set" "nitride" "")
(command "_layer" "set" "fda1" "")
(setq coords (list 
(list 640.5625 535.2246) 
(list 714.585 534.4746) 
(list 714.585 534.6516) 
(list 640.5625 535.3016)))
(apply 'command (append '("pline") coords '("c")))
(setq currobj (ssadd (entlast) currobj))
(setq coords (list 
(list 640.5625 535.4446) 
(list 714.585 534.7946) 
(list 714.585 534.9716) 
(list 640.5625 535.5216)))
(apply 'command (append '("pline") coords '("c")))
(setq currobj (ssadd (entlast) currobj))
(setq coords (list 
(list 640.5625 535.6646) 
(list 714.585 535.1146) 
(list 714.585 535.2916) 
(list 640.5625 535.7416)))
(apply 'command (append '("pline") coords '("c")))
(setq currobj (ssadd (entlast) currobj))
(setq coords (list 
(list 640.5625 535.8846) 
(list 714.585 535.4346) 
(list 714.585 535.6116) 
(list 640.5625 535.9616)))
(apply 'command (append '("pline") coords '("c")))
(setq currobj (ssadd (entlast) currobj))
(setq coords (list 
(list 640.5625 536.1046) 
(list 714.585 535.7546) 
(list 714.585 535.9316) 
(list 640.5625 536.1816)))
(apply 'command (append '("pline") coords '("c")))
(setq currobj (ssadd (entlast) currobj))
(setq coords (list 
(list 640.5625 536.3246) 
(list 714.585 536.0746) 
(list 714.585 536.2516) 
(list 640.5625 536.4016)))
(apply 'command (append '("pline") coords '("c")))
(setq currobj (ssadd (entlast) currobj))
(setq coords (list 
(list 640.5625 536.5446) 
(list 714.585 536.3946) 
(list 714.585 536.5716) 
(list 640.5625 536.6216)))
(apply 'command (append '("pline") coords '("c")))
(setq currobj (ssadd (entlast) currobj))
(setq coords (list 
(list 640.5625 536.7646) 
(list 714.585 536.7146) 
(list 714.585 536.8916) 
(list 640.5625 536.8416)))
(apply 'command (append '("pline") coords '("c")))
(setq currobj (ssadd (entlast) currobj))
(setq coords (list 
(list 640.5625 536.9846) 
(list 714.585 537.0346) 
(list 714.585 537.2116) 
(list 640.5625 537.0616)))
(apply 'command (append '("pline") coords '("c")))
(setq currobj (ssadd (entlast) currobj))
(setq coords (list 
(list 640.5625 537.2046) 
(list 714.585 537.3546) 
(list 714.585 537.5316) 
(list 640.5625 537.2816)))
(apply 'command (append '("pline") coords '("c")))
(setq currobj (ssadd (entlast) currobj))
(setq coords (list 
(list 640.5625 537.4246) 
(list 714.585 537.6746) 
(list 714.585 537.8516) 
(list 640.5625 537.5016)))
(apply 'command (append '("pline") coords '("c")))
(setq currobj (ssadd (entlast) currobj))
(setq coords (list 
(list 640.5625 537.6446) 
(list 714.585 537.9946) 
(list 714.585 538.1716) 
(list 640.5625 537.7216)))
(apply 'command (append '("pline") coords '("c")))
(setq currobj (ssadd (entlast) currobj))
(setq coords (list 
(list 640.5625 537.8646) 
(list 714.585 538.3146) 
(list 714.585 538.4916) 
(list 640.5625 537.9416)))
(apply 'command (append '("pline") coords '("c")))
(setq currobj (ssadd (entlast) currobj))
(setq coords (list 
(list 640.5625 538.0846) 
(list 714.585 538.6346) 
(list 714.585 538.8116) 
(list 640.5625 538.1616)))
(apply 'command (append '("pline") coords '("c")))
(setq currobj (ssadd (entlast) currobj))
(setq coords (list 
(list 640.5625 538.3046) 
(list 714.585 538.9546) 
(list 714.585 539.1316) 
(list 640.5625 538.3816)))
(apply 'command (append '("pline") coords '("c")))
(setq currobj (ssadd (entlast) currobj))
(setq coords (list 
(list 639.4375 538.3816) 
(list 565.415 539.1316) 
(list 565.415 538.9546) 
(list 639.4375 538.3046)))
(apply 'command (append '("pline") coords '("c")))
(setq currobj (ssadd (entlast) currobj))
(setq coords (list 
(list 639.4375 538.1616) 
(list 565.415 538.8116) 
(list 565.415 538.6346) 
(list 639.4375 538.0846)))
(apply 'command (append '("pline") coords '("c")))
(setq currobj (ssadd (entlast) currobj))
(setq coords (list 
(list 639.4375 537.9416) 
(list 565.415 538.4916) 
(list 565.415 538.3146) 
(list 639.4375 537.8646)))
(apply 'command (append '("pline") coords '("c")))
(setq currobj (ssadd (entlast) currobj))
(setq coords (list 
(list 639.4375 537.7216) 
(list 565.415 538.1716) 
(list 565.415 537.9946) 
(list 639.4375 537.6446)))
(apply 'command (append '("pline") coords '("c")))
(setq currobj (ssadd (entlast) currobj))
(setq coords (list 
(list 639.4375 537.5016) 
(list 565.415 537.8516) 
(list 565.415 537.6746) 
(list 639.4375 537.4246)))
(apply 'command (append '("pline") coords '("c")))
(setq currobj (ssadd (entlast) currobj))
(setq coords (list 
(list 639.4375 537.2816) 
(list 565.415 537.5316) 
(list 565.415 537.3546) 
(list 639.4375 537.2046)))
(apply 'command (append '("pline") coords '("c")))
(setq currobj (ssadd (entlast) currobj))
(setq coords (list 
(list 639.4375 537.0616) 
(list 565.415 537.2116) 
(list 565.415 537.0346) 
(list 639.4375 536.9846)))
(apply 'command (append '("pline") coords '("c")))
(setq currobj (ssadd (entlast) currobj))
(setq coords (list 
(list 639.4375 536.8416) 
(list 565.415 536.8916) 
(list 565.415 536.7146) 
(list 639.4375 536.7646)))
(apply 'command (append '("pline") coords '("c")))
(setq currobj (ssadd (entlast) currobj))
(setq coords (list 
(list 639.4375 536.6216) 
(list 565.415 536.5716) 
(list 565.415 536.3946) 
(list 639.4375 536.5446)))
(apply 'command (append '("pline") coords '("c")))
(setq currobj (ssadd (entlast) currobj))
(setq coords (list 
(list 639.4375 536.4016) 
(list 565.415 536.2516) 
(list 565.415 536.0746) 
(list 639.4375 536.3246)))
(apply 'command (append '("pline") coords '("c")))
(setq currobj (ssadd (entlast) currobj))
(setq coords (list 
(list 639.4375 536.1816) 
(list 565.415 535.9316) 
(list 565.415 535.7546) 
(list 639.4375 536.1046)))
(apply 'command (append '("pline") coords '("c")))
(setq currobj (ssadd (entlast) currobj))
(setq coords (list 
(list 639.4375 535.9616) 
(list 565.415 535.6116) 
(list 565.415 535.4346) 
(list 639.4375 535.8846)))
(apply 'command (append '("pline") coords '("c")))
(setq currobj (ssadd (entlast) currobj))
(setq coords (list 
(list 639.4375 535.7416) 
(list 565.415 535.2916) 
(list 565.415 535.1146) 
(list 639.4375 535.6646)))
(apply 'command (append '("pline") coords '("c")))
(setq currobj (ssadd (entlast) currobj))
(setq coords (list 
(list 639.4375 535.5216) 
(list 565.415 534.9716) 
(list 565.415 534.7946) 
(list 639.4375 535.4446)))
(apply 'command (append '("pline") coords '("c")))
(setq currobj (ssadd (entlast) currobj))
(setq coords (list 
(list 639.4375 535.3016) 
(list 565.415 534.6516) 
(list 565.415 534.4746) 
(list 639.4375 535.2246)))
(apply 'command (append '("pline") coords '("c")))
(setq currobj (ssadd (entlast) currobj))
(command "_layer" "set" "nitride" "")
(command "_layer" "set" "text" "")
(command "_circle" "639.0625,524.0816" "0.075")
(command "_circle" "639.0625,524.3816" "0.075")
(command "_circle" "639.0625,524.6816" "0.075")
(command "_circle" "639.0625,524.9816" "0.075")
(command "_circle" "639.0625,525.2816" "0.075")
(command "_circle" "638.7625,524.0816" "0.075")
(command "_circle" "638.7625,524.3816" "0.075")
(command "_circle" "638.7625,524.6816" "0.075")
(command "_circle" "638.7625,524.9816" "0.075")
(command "_circle" "638.7625,525.2816" "0.075")
(command "_circle" "638.4625,524.0816" "0.075")
(command "_circle" "638.4625,524.3816" "0.075")
(command "_circle" "638.4625,524.6816" "0.075")
(command "_circle" "638.4625,524.9816" "0.075")
(command "_circle" "638.4625,525.2816" "0.075")
(command "_circle" "638.1625,524.0816" "0.075")
(command "_circle" "638.1625,524.3816" "0.075")
(command "_circle" "638.1625,524.6816" "0.075")
(command "_circle" "638.1625,524.9816" "0.075")
(command "_circle" "638.1625,525.2816" "0.075")
(command "_circle" "637.8625,524.0816" "0.075")
(command "_circle" "637.8625,524.3816" "0.075")
(command "_circle" "637.8625,524.6816" "0.075")
(command "_circle" "637.8625,524.9816" "0.075")
(command "_circle" "637.8625,525.2816" "0.075")
(command "_layer" "set" "nitride" "")
(setq coords (list 
(list 640.2625 549.5246) 
(list 640.2625 665.1693) 
(list 639.7375 665.1693) 
(list 639.7375 549.5246)))
(apply 'command (append '("pline") coords '("c")))
(setq currobj (ssadd (entlast) currobj))
(command "_layer" "set" "prebias" "")
(command "_rectangle" "639.7375,549.5246" "640.2625,665.1693")
(setq currobj (ssadd (entlast) currobj))
(command "_layer" "set" "nitride" "")
(setq coords (list 
(list 640.2625 665.1693) 
(list 640.5625 675.1693) 
(list 640.5625 675.1693) 
(list 640.5625 676.1693) 
(list 714.585 675.4193) 
(list 714.585 680.3623) 
(list 640.5625 679.6123) 
(list 640.5625 680.6123) 
(list 640.5625 680.6123) 
(list 640.2625 690.6123) 
(list 639.7375 690.6123) 
(list 639.4375 680.6123) 
(list 639.4375 680.6123) 
(list 639.4375 679.6123) 
(list 565.415 680.3623) 
(list 565.415 675.4193) 
(list 639.4375 676.1693) 
(list 639.4375 675.1693) 
(list 639.4375 675.1693) 
(list 639.7375 665.1693)))
(apply 'command (append '("pline") coords '("c")))
(setq currobj (ssadd (entlast) currobj))
(command "_layer" "set" "prebias" "")
(setq coords (list 
(list 639.4375 665.1693) 
(list 639.4375 676.1693) 
(list 565.415 675.4193) 
(list 565.415 680.3623) 
(list 639.4375 679.6123) 
(list 639.4375 690.6123) 
(list 640.5625 690.6123) 
(list 640.5625 679.6123) 
(list 714.585 680.3623) 
(list 714.585 675.4193) 
(list 640.5625 676.1693) 
(list 640.5625 665.1693)))
(apply 'command (append '("pline") coords '("c")))
(setq currobj (ssadd (entlast) currobj))
(command "_layer" "set" "nitride" "")
(command "_layer" "set" "fda1" "")
(setq coords (list 
(list 640.5625 676.3123) 
(list 714.585 675.5623) 
(list 714.585 675.7393) 
(list 640.5625 676.3893)))
(apply 'command (append '("pline") coords '("c")))
(setq currobj (ssadd (entlast) currobj))
(setq coords (list 
(list 640.5625 676.5323) 
(list 714.585 675.8823) 
(list 714.585 676.0593) 
(list 640.5625 676.6093)))
(apply 'command (append '("pline") coords '("c")))
(setq currobj (ssadd (entlast) currobj))
(setq coords (list 
(list 640.5625 676.7523) 
(list 714.585 676.2023) 
(list 714.585 676.3793) 
(list 640.5625 676.8293)))
(apply 'command (append '("pline") coords '("c")))
(setq currobj (ssadd (entlast) currobj))
(setq coords (list 
(list 640.5625 676.9723) 
(list 714.585 676.5223) 
(list 714.585 676.6993) 
(list 640.5625 677.0493)))
(apply 'command (append '("pline") coords '("c")))
(setq currobj (ssadd (entlast) currobj))
(setq coords (list 
(list 640.5625 677.1923) 
(list 714.585 676.8423) 
(list 714.585 677.0193) 
(list 640.5625 677.2693)))
(apply 'command (append '("pline") coords '("c")))
(setq currobj (ssadd (entlast) currobj))
(setq coords (list 
(list 640.5625 677.4123) 
(list 714.585 677.1623) 
(list 714.585 677.3393) 
(list 640.5625 677.4893)))
(apply 'command (append '("pline") coords '("c")))
(setq currobj (ssadd (entlast) currobj))
(setq coords (list 
(list 640.5625 677.6323) 
(list 714.585 677.4823) 
(list 714.585 677.6593) 
(list 640.5625 677.7093)))
(apply 'command (append '("pline") coords '("c")))
(setq currobj (ssadd (entlast) currobj))
(setq coords (list 
(list 640.5625 677.8523) 
(list 714.585 677.8023) 
(list 714.585 677.9793) 
(list 640.5625 677.9293)))
(apply 'command (append '("pline") coords '("c")))
(setq currobj (ssadd (entlast) currobj))
(setq coords (list 
(list 640.5625 678.0723) 
(list 714.585 678.1223) 
(list 714.585 678.2993) 
(list 640.5625 678.1493)))
(apply 'command (append '("pline") coords '("c")))
(setq currobj (ssadd (entlast) currobj))
(setq coords (list 
(list 640.5625 678.2923) 
(list 714.585 678.4423) 
(list 714.585 678.6193) 
(list 640.5625 678.3693)))
(apply 'command (append '("pline") coords '("c")))
(setq currobj (ssadd (entlast) currobj))
(setq coords (list 
(list 640.5625 678.5123) 
(list 714.585 678.7623) 
(list 714.585 678.9393) 
(list 640.5625 678.5893)))
(apply 'command (append '("pline") coords '("c")))
(setq currobj (ssadd (entlast) currobj))
(setq coords (list 
(list 640.5625 678.7323) 
(list 714.585 679.0823) 
(list 714.585 679.2593) 
(list 640.5625 678.8093)))
(apply 'command (append '("pline") coords '("c")))
(setq currobj (ssadd (entlast) currobj))
(setq coords (list 
(list 640.5625 678.9523) 
(list 714.585 679.4023) 
(list 714.585 679.5793) 
(list 640.5625 679.0293)))
(apply 'command (append '("pline") coords '("c")))
(setq currobj (ssadd (entlast) currobj))
(setq coords (list 
(list 640.5625 679.1723) 
(list 714.585 679.7223) 
(list 714.585 679.8993) 
(list 640.5625 679.2493)))
(apply 'command (append '("pline") coords '("c")))
(setq currobj (ssadd (entlast) currobj))
(setq coords (list 
(list 640.5625 679.3923) 
(list 714.585 680.0423) 
(list 714.585 680.2193) 
(list 640.5625 679.4693)))
(apply 'command (append '("pline") coords '("c")))
(setq currobj (ssadd (entlast) currobj))
(setq coords (list 
(list 639.4375 679.4693) 
(list 565.415 680.2193) 
(list 565.415 680.0423) 
(list 639.4375 679.3923)))
(apply 'command (append '("pline") coords '("c")))
(setq currobj (ssadd (entlast) currobj))
(setq coords (list 
(list 639.4375 679.2493) 
(list 565.415 679.8993) 
(list 565.415 679.7223) 
(list 639.4375 679.1723)))
(apply 'command (append '("pline") coords '("c")))
(setq currobj (ssadd (entlast) currobj))
(setq coords (list 
(list 639.4375 679.0293) 
(list 565.415 679.5793) 
(list 565.415 679.4023) 
(list 639.4375 678.9523)))
(apply 'command (append '("pline") coords '("c")))
(setq currobj (ssadd (entlast) currobj))
(setq coords (list 
(list 639.4375 678.8093) 
(list 565.415 679.2593) 
(list 565.415 679.0823) 
(list 639.4375 678.7323)))
(apply 'command (append '("pline") coords '("c")))
(setq currobj (ssadd (entlast) currobj))
(setq coords (list 
(list 639.4375 678.5893) 
(list 565.415 678.9393) 
(list 565.415 678.7623) 
(list 639.4375 678.5123)))
(apply 'command (append '("pline") coords '("c")))
(setq currobj (ssadd (entlast) currobj))
(setq coords (list 
(list 639.4375 678.3693) 
(list 565.415 678.6193) 
(list 565.415 678.4423) 
(list 639.4375 678.2923)))
(apply 'command (append '("pline") coords '("c")))
(setq currobj (ssadd (entlast) currobj))
(setq coords (list 
(list 639.4375 678.1493) 
(list 565.415 678.2993) 
(list 565.415 678.1223) 
(list 639.4375 678.0723)))
(apply 'command (append '("pline") coords '("c")))
(setq currobj (ssadd (entlast) currobj))
(setq coords (list 
(list 639.4375 677.9293) 
(list 565.415 677.9793) 
(list 565.415 677.8023) 
(list 639.4375 677.8523)))
(apply 'command (append '("pline") coords '("c")))
(setq currobj (ssadd (entlast) currobj))
(setq coords (list 
(list 639.4375 677.7093) 
(list 565.415 677.6593) 
(list 565.415 677.4823) 
(list 639.4375 677.6323)))
(apply 'command (append '("pline") coords '("c")))
(setq currobj (ssadd (entlast) currobj))
(setq coords (list 
(list 639.4375 677.4893) 
(list 565.415 677.3393) 
(list 565.415 677.1623) 
(list 639.4375 677.4123)))
(apply 'command (append '("pline") coords '("c")))
(setq currobj (ssadd (entlast) currobj))
(setq coords (list 
(list 639.4375 677.2693) 
(list 565.415 677.0193) 
(list 565.415 676.8423) 
(list 639.4375 677.1923)))
(apply 'command (append '("pline") coords '("c")))
(setq currobj (ssadd (entlast) currobj))
(setq coords (list 
(list 639.4375 677.0493) 
(list 565.415 676.6993) 
(list 565.415 676.5223) 
(list 639.4375 676.9723)))
(apply 'command (append '("pline") coords '("c")))
(setq currobj (ssadd (entlast) currobj))
(setq coords (list 
(list 639.4375 676.8293) 
(list 565.415 676.3793) 
(list 565.415 676.2023) 
(list 639.4375 676.7523)))
(apply 'command (append '("pline") coords '("c")))
(setq currobj (ssadd (entlast) currobj))
(setq coords (list 
(list 639.4375 676.6093) 
(list 565.415 676.0593) 
(list 565.415 675.8823) 
(list 639.4375 676.5323)))
(apply 'command (append '("pline") coords '("c")))
(setq currobj (ssadd (entlast) currobj))
(setq coords (list 
(list 639.4375 676.3893) 
(list 565.415 675.7393) 
(list 565.415 675.5623) 
(list 639.4375 676.3123)))
(apply 'command (append '("pline") coords '("c")))
(setq currobj (ssadd (entlast) currobj))
(command "_layer" "set" "nitride" "")
(command "_layer" "set" "text" "")
(command "_circle" "639.0625,665.1693" "0.075")
(command "_circle" "639.0625,665.4693" "0.075")
(command "_circle" "639.0625,665.7693" "0.075")
(command "_circle" "639.0625,666.0693" "0.075")
(command "_circle" "639.0625,666.3693" "0.075")
(command "_circle" "638.7625,665.1693" "0.075")
(command "_circle" "638.7625,665.4693" "0.075")
(command "_circle" "638.7625,665.7693" "0.075")
(command "_circle" "638.7625,666.0693" "0.075")
(command "_circle" "638.7625,666.3693" "0.075")
(command "_circle" "638.4625,665.1693" "0.075")
(command "_circle" "638.4625,665.4693" "0.075")
(command "_circle" "638.4625,665.7693" "0.075")
(command "_circle" "638.4625,666.0693" "0.075")
(command "_circle" "638.4625,666.3693" "0.075")
(command "_circle" "638.1625,665.1693" "0.075")
(command "_circle" "638.1625,665.4693" "0.075")
(command "_circle" "638.1625,665.7693" "0.075")
(command "_circle" "638.1625,666.0693" "0.075")
(command "_circle" "638.1625,666.3693" "0.075")
(command "_circle" "637.8625,665.1693" "0.075")
(command "_circle" "637.8625,665.4693" "0.075")
(command "_circle" "637.8625,665.7693" "0.075")
(command "_circle" "637.8625,666.0693" "0.075")
(command "_circle" "637.8625,666.3693" "0.075")
(command "_layer" "set" "nitride" "")
(setq coords (list 
(list 640.2625 690.6123) 
(list 640.2625 806.257) 
(list 639.7375 806.257) 
(list 639.7375 690.6123)))
(apply 'command (append '("pline") coords '("c")))
(setq currobj (ssadd (entlast) currobj))
(command "_layer" "set" "prebias" "")
(command "_rectangle" "639.7375,690.6123" "640.2625,806.257")
(setq currobj (ssadd (entlast) currobj))
(command "_layer" "set" "nitride" "")
(setq coords (list 
(list 640.2625 806.257) 
(list 640.5625 816.257) 
(list 640.5625 816.257) 
(list 640.5625 817.257) 
(list 714.585 816.507) 
(list 714.585 821.45) 
(list 640.5625 820.7) 
(list 640.5625 821.7) 
(list 640.5625 821.7) 
(list 640.2625 831.7) 
(list 639.7375 831.7) 
(list 639.4375 821.7) 
(list 639.4375 821.7) 
(list 639.4375 820.7) 
(list 565.415 821.45) 
(list 565.415 816.507) 
(list 639.4375 817.257) 
(list 639.4375 816.257) 
(list 639.4375 816.257) 
(list 639.7375 806.257)))
(apply 'command (append '("pline") coords '("c")))
(setq currobj (ssadd (entlast) currobj))
(command "_layer" "set" "prebias" "")
(setq coords (list 
(list 639.4375 806.257) 
(list 639.4375 817.257) 
(list 565.415 816.507) 
(list 565.415 821.45) 
(list 639.4375 820.7) 
(list 639.4375 831.7) 
(list 640.5625 831.7) 
(list 640.5625 820.7) 
(list 714.585 821.45) 
(list 714.585 816.507) 
(list 640.5625 817.257) 
(list 640.5625 806.257)))
(apply 'command (append '("pline") coords '("c")))
(setq currobj (ssadd (entlast) currobj))
(command "_layer" "set" "nitride" "")
(command "_layer" "set" "fda1" "")
(setq coords (list 
(list 640.5625 817.4) 
(list 714.585 816.65) 
(list 714.585 816.827) 
(list 640.5625 817.477)))
(apply 'command (append '("pline") coords '("c")))
(setq currobj (ssadd (entlast) currobj))
(setq coords (list 
(list 640.5625 817.62) 
(list 714.585 816.97) 
(list 714.585 817.147) 
(list 640.5625 817.697)))
(apply 'command (append '("pline") coords '("c")))
(setq currobj (ssadd (entlast) currobj))
(setq coords (list 
(list 640.5625 817.84) 
(list 714.585 817.29) 
(list 714.585 817.467) 
(list 640.5625 817.917)))
(apply 'command (append '("pline") coords '("c")))
(setq currobj (ssadd (entlast) currobj))
(setq coords (list 
(list 640.5625 818.06) 
(list 714.585 817.61) 
(list 714.585 817.787) 
(list 640.5625 818.137)))
(apply 'command (append '("pline") coords '("c")))
(setq currobj (ssadd (entlast) currobj))
(setq coords (list 
(list 640.5625 818.28) 
(list 714.585 817.93) 
(list 714.585 818.107) 
(list 640.5625 818.357)))
(apply 'command (append '("pline") coords '("c")))
(setq currobj (ssadd (entlast) currobj))
(setq coords (list 
(list 640.5625 818.5) 
(list 714.585 818.25) 
(list 714.585 818.427) 
(list 640.5625 818.577)))
(apply 'command (append '("pline") coords '("c")))
(setq currobj (ssadd (entlast) currobj))
(setq coords (list 
(list 640.5625 818.72) 
(list 714.585 818.57) 
(list 714.585 818.747) 
(list 640.5625 818.797)))
(apply 'command (append '("pline") coords '("c")))
(setq currobj (ssadd (entlast) currobj))
(setq coords (list 
(list 640.5625 818.94) 
(list 714.585 818.89) 
(list 714.585 819.067) 
(list 640.5625 819.017)))
(apply 'command (append '("pline") coords '("c")))
(setq currobj (ssadd (entlast) currobj))
(setq coords (list 
(list 640.5625 819.16) 
(list 714.585 819.21) 
(list 714.585 819.387) 
(list 640.5625 819.237)))
(apply 'command (append '("pline") coords '("c")))
(setq currobj (ssadd (entlast) currobj))
(setq coords (list 
(list 640.5625 819.38) 
(list 714.585 819.53) 
(list 714.585 819.707) 
(list 640.5625 819.457)))
(apply 'command (append '("pline") coords '("c")))
(setq currobj (ssadd (entlast) currobj))
(setq coords (list 
(list 640.5625 819.6) 
(list 714.585 819.85) 
(list 714.585 820.027) 
(list 640.5625 819.677)))
(apply 'command (append '("pline") coords '("c")))
(setq currobj (ssadd (entlast) currobj))
(setq coords (list 
(list 640.5625 819.82) 
(list 714.585 820.17) 
(list 714.585 820.347) 
(list 640.5625 819.897)))
(apply 'command (append '("pline") coords '("c")))
(setq currobj (ssadd (entlast) currobj))
(setq coords (list 
(list 640.5625 820.04) 
(list 714.585 820.49) 
(list 714.585 820.667) 
(list 640.5625 820.117)))
(apply 'command (append '("pline") coords '("c")))
(setq currobj (ssadd (entlast) currobj))
(setq coords (list 
(list 640.5625 820.26) 
(list 714.585 820.81) 
(list 714.585 820.987) 
(list 640.5625 820.337)))
(apply 'command (append '("pline") coords '("c")))
(setq currobj (ssadd (entlast) currobj))
(setq coords (list 
(list 640.5625 820.48) 
(list 714.585 821.13) 
(list 714.585 821.307) 
(list 640.5625 820.557)))
(apply 'command (append '("pline") coords '("c")))
(setq currobj (ssadd (entlast) currobj))
(setq coords (list 
(list 639.4375 820.557) 
(list 565.415 821.307) 
(list 565.415 821.13) 
(list 639.4375 820.48)))
(apply 'command (append '("pline") coords '("c")))
(setq currobj (ssadd (entlast) currobj))
(setq coords (list 
(list 639.4375 820.337) 
(list 565.415 820.987) 
(list 565.415 820.81) 
(list 639.4375 820.26)))
(apply 'command (append '("pline") coords '("c")))
(setq currobj (ssadd (entlast) currobj))
(setq coords (list 
(list 639.4375 820.117) 
(list 565.415 820.667) 
(list 565.415 820.49) 
(list 639.4375 820.04)))
(apply 'command (append '("pline") coords '("c")))
(setq currobj (ssadd (entlast) currobj))
(setq coords (list 
(list 639.4375 819.897) 
(list 565.415 820.347) 
(list 565.415 820.17) 
(list 639.4375 819.82)))
(apply 'command (append '("pline") coords '("c")))
(setq currobj (ssadd (entlast) currobj))
(setq coords (list 
(list 639.4375 819.677) 
(list 565.415 820.027) 
(list 565.415 819.85) 
(list 639.4375 819.6)))
(apply 'command (append '("pline") coords '("c")))
(setq currobj (ssadd (entlast) currobj))
(setq coords (list 
(list 639.4375 819.457) 
(list 565.415 819.707) 
(list 565.415 819.53) 
(list 639.4375 819.38)))
(apply 'command (append '("pline") coords '("c")))
(setq currobj (ssadd (entlast) currobj))
(setq coords (list 
(list 639.4375 819.237) 
(list 565.415 819.387) 
(list 565.415 819.21) 
(list 639.4375 819.16)))
(apply 'command (append '("pline") coords '("c")))
(setq currobj (ssadd (entlast) currobj))
(setq coords (list 
(list 639.4375 819.017) 
(list 565.415 819.067) 
(list 565.415 818.89) 
(list 639.4375 818.94)))
(apply 'command (append '("pline") coords '("c")))
(setq currobj (ssadd (entlast) currobj))
(setq coords (list 
(list 639.4375 818.797) 
(list 565.415 818.747) 
(list 565.415 818.57) 
(list 639.4375 818.72)))
(apply 'command (append '("pline") coords '("c")))
(setq currobj (ssadd (entlast) currobj))
(setq coords (list 
(list 639.4375 818.577) 
(list 565.415 818.427) 
(list 565.415 818.25) 
(list 639.4375 818.5)))
(apply 'command (append '("pline") coords '("c")))
(setq currobj (ssadd (entlast) currobj))
(setq coords (list 
(list 639.4375 818.357) 
(list 565.415 818.107) 
(list 565.415 817.93) 
(list 639.4375 818.28)))
(apply 'command (append '("pline") coords '("c")))
(setq currobj (ssadd (entlast) currobj))
(setq coords (list 
(list 639.4375 818.137) 
(list 565.415 817.787) 
(list 565.415 817.61) 
(list 639.4375 818.06)))
(apply 'command (append '("pline") coords '("c")))
(setq currobj (ssadd (entlast) currobj))
(setq coords (list 
(list 639.4375 817.917) 
(list 565.415 817.467) 
(list 565.415 817.29) 
(list 639.4375 817.84)))
(apply 'command (append '("pline") coords '("c")))
(setq currobj (ssadd (entlast) currobj))
(setq coords (list 
(list 639.4375 817.697) 
(list 565.415 817.147) 
(list 565.415 816.97) 
(list 639.4375 817.62)))
(apply 'command (append '("pline") coords '("c")))
(setq currobj (ssadd (entlast) currobj))
(setq coords (list 
(list 639.4375 817.477) 
(list 565.415 816.827) 
(list 565.415 816.65) 
(list 639.4375 817.4)))
(apply 'command (append '("pline") coords '("c")))
(setq currobj (ssadd (entlast) currobj))
(command "_layer" "set" "nitride" "")
(command "_layer" "set" "text" "")
(command "_circle" "639.0625,806.257" "0.075")
(command "_circle" "639.0625,806.557" "0.075")
(command "_circle" "639.0625,806.857" "0.075")
(command "_circle" "639.0625,807.157" "0.075")
(command "_circle" "639.0625,807.457" "0.075")
(command "_circle" "638.7625,806.257" "0.075")
(command "_circle" "638.7625,806.557" "0.075")
(command "_circle" "638.7625,806.857" "0.075")
(command "_circle" "638.7625,807.157" "0.075")
(command "_circle" "638.7625,807.457" "0.075")
(command "_circle" "638.4625,806.257" "0.075")
(command "_circle" "638.4625,806.557" "0.075")
(command "_circle" "638.4625,806.857" "0.075")
(command "_circle" "638.4625,807.157" "0.075")
(command "_circle" "638.4625,807.457" "0.075")
(command "_circle" "638.1625,806.257" "0.075")
(command "_circle" "638.1625,806.557" "0.075")
(command "_circle" "638.1625,806.857" "0.075")
(command "_circle" "638.1625,807.157" "0.075")
(command "_circle" "638.1625,807.457" "0.075")
(command "_circle" "637.8625,806.257" "0.075")
(command "_circle" "637.8625,806.557" "0.075")
(command "_circle" "637.8625,806.857" "0.075")
(command "_circle" "637.8625,807.157" "0.075")
(command "_circle" "637.8625,807.457" "0.075")
(command "_layer" "set" "nitride" "")
(setq coords (list 
(list 640.2625 831.7) 
(list 640.2625 836.7) 
(list 639.7375 836.7) 
(list 639.7375 831.7)))
(apply 'command (append '("pline") coords '("c")))
(setq currobj (ssadd (entlast) currobj))
(command "_layer" "set" "prebias" "")
(command "_rectangle" "639.7375,831.7" "640.2625,836.7")
(setq currobj (ssadd (entlast) currobj))
(command "_layer" "set" "nitride" "")
(setq cooledsinglenanobeam2 currobj)
(setq currobj nil)
(setq currobj (ssadd))
; DRAWING PHOTONIC CRYSTAL
(command "_layer" "set" "negYjunc" "")
(setq coords (list 
(list 640.135 866.7) 
(list 640 851.7) 
(list 640 866.7)))
(apply 'command (append '("pline") coords '("c")))
(setq currobj (ssadd (entlast) currobj))
(setq coords (list 
(list 640.2625 836.7) 
(list 640.415 866.7) 
(list 641.123 866.7) 
(list 641.123 836.7)))
(apply 'command (append '("pline") coords '("c")))
(setq currobj (ssadd (entlast) currobj))
(setq coords (list 
(list 639.865 866.7) 
(list 640 851.7) 
(list 640 866.7)))
(apply 'command (append '("pline") coords '("c")))
(setq currobj (ssadd (entlast) currobj))
(setq coords (list 
(list 639.7375 836.7) 
(list 639.585 866.7) 
(list 638.877 866.7) 
(list 638.877 836.7)))
(apply 'command (append '("pline") coords '("c")))
(setq currobj (ssadd (entlast) currobj))
(command "_layer" "set" "nitride" "")
(setq yjunction2 currobj)
(setq currobj nil)
(setq currobj (ssadd))
(setq tap2 nil)
(setq tap2 (ssadd))
(command "_layer" "set" "phc" "")
(setq coords (list 
(list 640 866.7) 
(list 640.135 866.7) 
(list 640.135 866.7103) 
(list 640.135 866.7206) 
(list 640.135 866.7308) 
(list 640.135 866.7411) 
(list 640.135 866.7514) 
(list 640.135 866.7617) 
(list 640.135 866.7719) 
(list 640.135 866.7822) 
(list 640.135 866.7925) 
(list 640.135 866.8028) 
(list 640.135 866.8131) 
(list 640.135 866.8233) 
(list 640.135 866.8336) 
(list 640.135 866.8439) 
(list 640.135 866.8542) 
(list 640.135 866.8644) 
(list 640.135 866.8747) 
(list 640.135 866.885) 
(list 640.135 866.8953) 
(list 640.135 866.9056) 
(list 640.135 866.9158) 
(list 640.135 866.9261) 
(list 640.135 866.9364) 
(list 640.135 866.9467) 
(list 640.135 866.9569) 
(list 640.135 866.9672) 
(list 640.135 866.9775) 
(list 640.135 866.9878) 
(list 640.135 866.9981) 
(list 640.135 867.0083) 
(list 640.135 867.0186) 
(list 640.135 867.0289) 
(list 640.135 867.0392) 
(list 640.135 867.0494) 
(list 640.135 867.0597) 
(list 640.135 867.07) 
(list 640 867.07)))
(apply 'command (append '("pline") coords '("c")))
(setq tap2 (ssadd (entlast) tap2))
(command "_mirror" (entlast) "" "640,900" "640,901" "No")
(setq tap2 (ssadd (entlast) tap2))
(setq coords (list 
(list 640.4248 866.7) 
(list 640.415 866.7) 
(list 640.4153 866.7103) 
(list 640.4155 866.7206) 
(list 640.4157 866.7308) 
(list 640.4159 866.7411) 
(list 640.4159 866.7514) 
(list 640.4159 866.7617) 
(list 640.4158 866.7719) 
(list 640.4155 866.7822) 
(list 640.4152 866.7925) 
(list 640.4148 866.8028) 
(list 640.4143 866.8131) 
(list 640.4138 866.8233) 
(list 640.4132 866.8336) 
(list 640.4126 866.8439) 
(list 640.4121 866.8542) 
(list 640.4116 866.8644) 
(list 640.4112 866.8747) 
(list 640.4109 866.885) 
(list 640.4108 866.8953) 
(list 640.4108 866.9056) 
(list 640.4109 866.9158) 
(list 640.4113 866.9261) 
(list 640.4118 866.9364) 
(list 640.4125 866.9467) 
(list 640.4134 866.9569) 
(list 640.4145 866.9672) 
(list 640.4156 866.9775) 
(list 640.4168 866.9878) 
(list 640.4181 866.9981) 
(list 640.4194 867.0083) 
(list 640.4207 867.0186) 
(list 640.4218 867.0289) 
(list 640.4229 867.0392) 
(list 640.4237 867.0494) 
(list 640.4244 867.0597) 
(list 640.4248 867.07) 
(list 640.4248 867.07)))
(apply 'command (append '("pline") coords '("c")))
(setq tap2 (ssadd (entlast) tap2))
(command "_mirror" (entlast) "" "640,900" "640,901" "No")
(setq tap2 (ssadd (entlast) tap2))
(setq coords (list 
(list 641.123 866.7) 
(list 640.4248 866.7) 
(list 640.4248 866.7103) 
(list 640.4248 866.7206) 
(list 640.4248 866.7308) 
(list 640.4248 866.7411) 
(list 640.4248 866.7514) 
(list 640.4248 866.7617) 
(list 640.4248 866.7719) 
(list 640.4248 866.7822) 
(list 640.4248 866.7925) 
(list 640.4248 866.8028) 
(list 640.4248 866.8131) 
(list 640.4248 866.8233) 
(list 640.4248 866.8336) 
(list 640.4248 866.8439) 
(list 640.4248 866.8542) 
(list 640.4248 866.8644) 
(list 640.4248 866.8747) 
(list 640.4248 866.885) 
(list 640.4248 866.8953) 
(list 640.4248 866.9056) 
(list 640.4248 866.9158) 
(list 640.4248 866.9261) 
(list 640.4248 866.9364) 
(list 640.4248 866.9467) 
(list 640.4248 866.9569) 
(list 640.4248 866.9672) 
(list 640.4248 866.9775) 
(list 640.4248 866.9878) 
(list 640.4248 866.9981) 
(list 640.4248 867.0083) 
(list 640.4248 867.0186) 
(list 640.4248 867.0289) 
(list 640.4248 867.0392) 
(list 640.4248 867.0494) 
(list 640.4248 867.0597) 
(list 640.4248 867.07) 
(list 641.123 867.07)))
(apply 'command (append '("pline") coords '("c")))
(setq tap2 (ssadd (entlast) tap2))
(command "_mirror" (entlast) "" "640,900" "640,901" "No")
(setq tap2 (ssadd (entlast) tap2))
(setq coords (list 
(list 640 867.07) 
(list 640.135 867.07) 
(list 640.135 867.0803) 
(list 640.135 867.0906) 
(list 640.135 867.1008) 
(list 640.135 867.1111) 
(list 640.135 867.1214) 
(list 640.135 867.1317) 
(list 640.135 867.1419) 
(list 640.135 867.1522) 
(list 640.135 867.1625) 
(list 640.135 867.1728) 
(list 640.135 867.1831) 
(list 640.135 867.1933) 
(list 640.135 867.2036) 
(list 640.135 867.2139) 
(list 640.135 867.2242) 
(list 640.135 867.2344) 
(list 640.135 867.2447) 
(list 640.135 867.255) 
(list 640.135 867.2653) 
(list 640.135 867.2756) 
(list 640.135 867.2858) 
(list 640.135 867.2961) 
(list 640.135 867.3064) 
(list 640.135 867.3167) 
(list 640.135 867.3269) 
(list 640.135 867.3372) 
(list 640.135 867.3475) 
(list 640.135 867.3578) 
(list 640.135 867.3681) 
(list 640.135 867.3783) 
(list 640.135 867.3886) 
(list 640.135 867.3989) 
(list 640.135 867.4092) 
(list 640.135 867.4194) 
(list 640.135 867.4297) 
(list 640.135 867.44) 
(list 640 867.44)))
(apply 'command (append '("pline") coords '("c")))
(setq tap2 (ssadd (entlast) tap2))
(command "_mirror" (entlast) "" "640,900" "640,901" "No")
(setq tap2 (ssadd (entlast) tap2))
(setq coords (list 
(list 640.4345 867.07) 
(list 640.4248 867.07) 
(list 640.4249 867.0803) 
(list 640.4247 867.0906) 
(list 640.4243 867.1008) 
(list 640.4235 867.1111) 
(list 640.4225 867.1214) 
(list 640.4212 867.1317) 
(list 640.4196 867.1419) 
(list 640.4179 867.1522) 
(list 640.416 867.1625) 
(list 640.414 867.1728) 
(list 640.412 867.1831) 
(list 640.4101 867.1933) 
(list 640.4082 867.2036) 
(list 640.4066 867.2139) 
(list 640.4051 867.2242) 
(list 640.404 867.2344) 
(list 640.4032 867.2447) 
(list 640.4027 867.255) 
(list 640.4027 867.2653) 
(list 640.4031 867.2756) 
(list 640.404 867.2858) 
(list 640.4052 867.2961) 
(list 640.4069 867.3064) 
(list 640.4089 867.3167) 
(list 640.4112 867.3269) 
(list 640.4137 867.3372) 
(list 640.4164 867.3475) 
(list 640.4192 867.3578) 
(list 640.422 867.3681) 
(list 640.4247 867.3783) 
(list 640.4272 867.3886) 
(list 640.4295 867.3989) 
(list 640.4314 867.4092) 
(list 640.4329 867.4194) 
(list 640.434 867.4297) 
(list 640.4345 867.44) 
(list 640.4345 867.44)))
(apply 'command (append '("pline") coords '("c")))
(setq tap2 (ssadd (entlast) tap2))
(command "_mirror" (entlast) "" "640,900" "640,901" "No")
(setq tap2 (ssadd (entlast) tap2))
(setq coords (list 
(list 641.123 867.07) 
(list 640.4345 867.07) 
(list 640.4345 867.0803) 
(list 640.4345 867.0906) 
(list 640.4345 867.1008) 
(list 640.4345 867.1111) 
(list 640.4345 867.1214) 
(list 640.4345 867.1317) 
(list 640.4345 867.1419) 
(list 640.4345 867.1522) 
(list 640.4345 867.1625) 
(list 640.4345 867.1728) 
(list 640.4345 867.1831) 
(list 640.4345 867.1933) 
(list 640.4345 867.2036) 
(list 640.4345 867.2139) 
(list 640.4345 867.2242) 
(list 640.4345 867.2344) 
(list 640.4345 867.2447) 
(list 640.4345 867.255) 
(list 640.4345 867.2653) 
(list 640.4345 867.2756) 
(list 640.4345 867.2858) 
(list 640.4345 867.2961) 
(list 640.4345 867.3064) 
(list 640.4345 867.3167) 
(list 640.4345 867.3269) 
(list 640.4345 867.3372) 
(list 640.4345 867.3475) 
(list 640.4345 867.3578) 
(list 640.4345 867.3681) 
(list 640.4345 867.3783) 
(list 640.4345 867.3886) 
(list 640.4345 867.3989) 
(list 640.4345 867.4092) 
(list 640.4345 867.4194) 
(list 640.4345 867.4297) 
(list 640.4345 867.44) 
(list 641.123 867.44)))
(apply 'command (append '("pline") coords '("c")))
(setq tap2 (ssadd (entlast) tap2))
(command "_mirror" (entlast) "" "640,900" "640,901" "No")
(setq tap2 (ssadd (entlast) tap2))
(setq coords (list 
(list 640 867.44) 
(list 640.135 867.44) 
(list 640.135 867.4503) 
(list 640.135 867.4606) 
(list 640.135 867.4708) 
(list 640.135 867.4811) 
(list 640.135 867.4914) 
(list 640.135 867.5017) 
(list 640.135 867.5119) 
(list 640.135 867.5222) 
(list 640.135 867.5325) 
(list 640.135 867.5428) 
(list 640.135 867.5531) 
(list 640.135 867.5633) 
(list 640.135 867.5736) 
(list 640.135 867.5839) 
(list 640.135 867.5942) 
(list 640.135 867.6044) 
(list 640.135 867.6147) 
(list 640.135 867.625) 
(list 640.135 867.6353) 
(list 640.135 867.6456) 
(list 640.135 867.6558) 
(list 640.135 867.6661) 
(list 640.135 867.6764) 
(list 640.135 867.6867) 
(list 640.135 867.6969) 
(list 640.135 867.7072) 
(list 640.135 867.7175) 
(list 640.135 867.7278) 
(list 640.135 867.7381) 
(list 640.135 867.7483) 
(list 640.135 867.7586) 
(list 640.135 867.7689) 
(list 640.135 867.7792) 
(list 640.135 867.7894) 
(list 640.135 867.7997) 
(list 640.135 867.81) 
(list 640 867.81)))
(apply 'command (append '("pline") coords '("c")))
(setq tap2 (ssadd (entlast) tap2))
(command "_mirror" (entlast) "" "640,900" "640,901" "No")
(setq tap2 (ssadd (entlast) tap2))
(setq coords (list 
(list 640.4443 867.44) 
(list 640.4345 867.44) 
(list 640.4345 867.4503) 
(list 640.434 867.4606) 
(list 640.4328 867.4708) 
(list 640.4312 867.4811) 
(list 640.429 867.4914) 
(list 640.4264 867.5017) 
(list 640.4235 867.5119) 
(list 640.4202 867.5222) 
(list 640.4168 867.5325) 
(list 640.4133 867.5428) 
(list 640.4098 867.5531) 
(list 640.4064 867.5633) 
(list 640.4033 867.5736) 
(list 640.4005 867.5839) 
(list 640.3982 867.5942) 
(list 640.3964 867.6044) 
(list 640.3951 867.6147) 
(list 640.3946 867.625) 
(list 640.3947 867.6353) 
(list 640.3955 867.6456) 
(list 640.397 867.6558) 
(list 640.3992 867.6661) 
(list 640.4019 867.6764) 
(list 640.4052 867.6867) 
(list 640.4089 867.6969) 
(list 640.4129 867.7072) 
(list 640.4172 867.7175) 
(list 640.4215 867.7278) 
(list 640.4258 867.7381) 
(list 640.43 867.7483) 
(list 640.4338 867.7586) 
(list 640.4372 867.7689) 
(list 640.44 867.7792) 
(list 640.4422 867.7894) 
(list 640.4436 867.7997) 
(list 640.4443 867.81) 
(list 640.4443 867.81)))
(apply 'command (append '("pline") coords '("c")))
(setq tap2 (ssadd (entlast) tap2))
(command "_mirror" (entlast) "" "640,900" "640,901" "No")
(setq tap2 (ssadd (entlast) tap2))
(setq coords (list 
(list 641.123 867.44) 
(list 640.4443 867.44) 
(list 640.4443 867.4503) 
(list 640.4443 867.4606) 
(list 640.4443 867.4708) 
(list 640.4443 867.4811) 
(list 640.4443 867.4914) 
(list 640.4443 867.5017) 
(list 640.4443 867.5119) 
(list 640.4443 867.5222) 
(list 640.4443 867.5325) 
(list 640.4443 867.5428) 
(list 640.4443 867.5531) 
(list 640.4443 867.5633) 
(list 640.4443 867.5736) 
(list 640.4443 867.5839) 
(list 640.4443 867.5942) 
(list 640.4443 867.6044) 
(list 640.4443 867.6147) 
(list 640.4443 867.625) 
(list 640.4443 867.6353) 
(list 640.4443 867.6456) 
(list 640.4443 867.6558) 
(list 640.4443 867.6661) 
(list 640.4443 867.6764) 
(list 640.4443 867.6867) 
(list 640.4443 867.6969) 
(list 640.4443 867.7072) 
(list 640.4443 867.7175) 
(list 640.4443 867.7278) 
(list 640.4443 867.7381) 
(list 640.4443 867.7483) 
(list 640.4443 867.7586) 
(list 640.4443 867.7689) 
(list 640.4443 867.7792) 
(list 640.4443 867.7894) 
(list 640.4443 867.7997) 
(list 640.4443 867.81) 
(list 641.123 867.81)))
(apply 'command (append '("pline") coords '("c")))
(setq tap2 (ssadd (entlast) tap2))
(command "_mirror" (entlast) "" "640,900" "640,901" "No")
(setq tap2 (ssadd (entlast) tap2))
(setq coords (list 
(list 640 867.81) 
(list 640.135 867.81) 
(list 640.135 867.8203) 
(list 640.135 867.8306) 
(list 640.135 867.8408) 
(list 640.135 867.8511) 
(list 640.135 867.8614) 
(list 640.135 867.8717) 
(list 640.135 867.8819) 
(list 640.135 867.8922) 
(list 640.135 867.9025) 
(list 640.135 867.9128) 
(list 640.135 867.9231) 
(list 640.135 867.9333) 
(list 640.135 867.9436) 
(list 640.135 867.9539) 
(list 640.135 867.9642) 
(list 640.135 867.9744) 
(list 640.135 867.9847) 
(list 640.135 867.995) 
(list 640.135 868.0053) 
(list 640.135 868.0156) 
(list 640.135 868.0258) 
(list 640.135 868.0361) 
(list 640.135 868.0464) 
(list 640.135 868.0567) 
(list 640.135 868.0669) 
(list 640.135 868.0772) 
(list 640.135 868.0875) 
(list 640.135 868.0978) 
(list 640.135 868.1081) 
(list 640.135 868.1183) 
(list 640.135 868.1286) 
(list 640.135 868.1389) 
(list 640.135 868.1492) 
(list 640.135 868.1594) 
(list 640.135 868.1697) 
(list 640.135 868.18) 
(list 640 868.18)))
(apply 'command (append '("pline") coords '("c")))
(setq tap2 (ssadd (entlast) tap2))
(command "_mirror" (entlast) "" "640,900" "640,901" "No")
(setq tap2 (ssadd (entlast) tap2))
(setq coords (list 
(list 640.4541 867.81) 
(list 640.4443 867.81) 
(list 640.4442 867.8203) 
(list 640.4432 867.8306) 
(list 640.4414 867.8408) 
(list 640.4389 867.8511) 
(list 640.4356 867.8614) 
(list 640.4317 867.8717) 
(list 640.4274 867.8819) 
(list 640.4226 867.8922) 
(list 640.4176 867.9025) 
(list 640.4125 867.9128) 
(list 640.4075 867.9231) 
(list 640.4027 867.9333) 
(list 640.3983 867.9436) 
(list 640.3944 867.9539) 
(list 640.3912 867.9642) 
(list 640.3887 867.9744) 
(list 640.3871 867.9847) 
(list 640.3864 867.995) 
(list 640.3867 868.0053) 
(list 640.3879 868.0156) 
(list 640.39 868.0258) 
(list 640.3931 868.0361) 
(list 640.3969 868.0464) 
(list 640.4015 868.0567) 
(list 640.4066 868.0669) 
(list 640.4122 868.0772) 
(list 640.418 868.0875) 
(list 640.4239 868.0978) 
(list 640.4297 868.1081) 
(list 640.4353 868.1183) 
(list 640.4403 868.1286) 
(list 640.4448 868.1389) 
(list 640.4485 868.1492) 
(list 640.4514 868.1594) 
(list 640.4533 868.1697) 
(list 640.4541 868.18) 
(list 640.4541 868.18)))
(apply 'command (append '("pline") coords '("c")))
(setq tap2 (ssadd (entlast) tap2))
(command "_mirror" (entlast) "" "640,900" "640,901" "No")
(setq tap2 (ssadd (entlast) tap2))
(setq coords (list 
(list 641.123 867.81) 
(list 640.4541 867.81) 
(list 640.4541 867.8203) 
(list 640.4541 867.8306) 
(list 640.4541 867.8408) 
(list 640.4541 867.8511) 
(list 640.4541 867.8614) 
(list 640.4541 867.8717) 
(list 640.4541 867.8819) 
(list 640.4541 867.8922) 
(list 640.4541 867.9025) 
(list 640.4541 867.9128) 
(list 640.4541 867.9231) 
(list 640.4541 867.9333) 
(list 640.4541 867.9436) 
(list 640.4541 867.9539) 
(list 640.4541 867.9642) 
(list 640.4541 867.9744) 
(list 640.4541 867.9847) 
(list 640.4541 867.995) 
(list 640.4541 868.0053) 
(list 640.4541 868.0156) 
(list 640.4541 868.0258) 
(list 640.4541 868.0361) 
(list 640.4541 868.0464) 
(list 640.4541 868.0567) 
(list 640.4541 868.0669) 
(list 640.4541 868.0772) 
(list 640.4541 868.0875) 
(list 640.4541 868.0978) 
(list 640.4541 868.1081) 
(list 640.4541 868.1183) 
(list 640.4541 868.1286) 
(list 640.4541 868.1389) 
(list 640.4541 868.1492) 
(list 640.4541 868.1594) 
(list 640.4541 868.1697) 
(list 640.4541 868.18) 
(list 641.123 868.18)))
(apply 'command (append '("pline") coords '("c")))
(setq tap2 (ssadd (entlast) tap2))
(command "_mirror" (entlast) "" "640,900" "640,901" "No")
(setq tap2 (ssadd (entlast) tap2))
(setq coords (list 
(list 640 868.18) 
(list 640.135 868.18) 
(list 640.135 868.1903) 
(list 640.135 868.2006) 
(list 640.135 868.2108) 
(list 640.135 868.2211) 
(list 640.135 868.2314) 
(list 640.135 868.2417) 
(list 640.135 868.2519) 
(list 640.135 868.2622) 
(list 640.135 868.2725) 
(list 640.135 868.2828) 
(list 640.135 868.2931) 
(list 640.135 868.3033) 
(list 640.135 868.3136) 
(list 640.135 868.3239) 
(list 640.135 868.3342) 
(list 640.135 868.3444) 
(list 640.135 868.3547) 
(list 640.135 868.365) 
(list 640.135 868.3753) 
(list 640.135 868.3856) 
(list 640.135 868.3958) 
(list 640.135 868.4061) 
(list 640.135 868.4164) 
(list 640.135 868.4267) 
(list 640.135 868.4369) 
(list 640.135 868.4472) 
(list 640.135 868.4575) 
(list 640.135 868.4678) 
(list 640.135 868.4781) 
(list 640.135 868.4883) 
(list 640.135 868.4986) 
(list 640.135 868.5089) 
(list 640.135 868.5192) 
(list 640.135 868.5294) 
(list 640.135 868.5397) 
(list 640.135 868.55) 
(list 640 868.55)))
(apply 'command (append '("pline") coords '("c")))
(setq tap2 (ssadd (entlast) tap2))
(command "_mirror" (entlast) "" "640,900" "640,901" "No")
(setq tap2 (ssadd (entlast) tap2))
(setq coords (list 
(list 640.4638 868.18) 
(list 640.4541 868.18) 
(list 640.4538 868.1903) 
(list 640.4524 868.2006) 
(list 640.45 868.2108) 
(list 640.4465 868.2211) 
(list 640.4422 868.2314) 
(list 640.437 868.2417) 
(list 640.4312 868.2519) 
(list 640.425 868.2622) 
(list 640.4184 868.2725) 
(list 640.4118 868.2828) 
(list 640.4052 868.2931) 
(list 640.399 868.3033) 
(list 640.3934 868.3136) 
(list 640.3884 868.3239) 
(list 640.3842 868.3342) 
(list 640.3811 868.3444) 
(list 640.3791 868.3547) 
(list 640.3782 868.365) 
(list 640.3786 868.3753) 
(list 640.3803 868.3856) 
(list 640.3831 868.3958) 
(list 640.387 868.4061) 
(list 640.392 868.4164) 
(list 640.3978 868.4267) 
(list 640.4044 868.4369) 
(list 640.4114 868.4472) 
(list 640.4188 868.4575) 
(list 640.4263 868.4678) 
(list 640.4336 868.4781) 
(list 640.4405 868.4883) 
(list 640.4469 868.4986) 
(list 640.4525 868.5089) 
(list 640.4571 868.5192) 
(list 640.4606 868.5294) 
(list 640.4629 868.5397) 
(list 640.4638 868.55) 
(list 640.4638 868.55)))
(apply 'command (append '("pline") coords '("c")))
(setq tap2 (ssadd (entlast) tap2))
(command "_mirror" (entlast) "" "640,900" "640,901" "No")
(setq tap2 (ssadd (entlast) tap2))
(setq coords (list 
(list 641.123 868.18) 
(list 640.4638 868.18) 
(list 640.4638 868.1903) 
(list 640.4638 868.2006) 
(list 640.4638 868.2108) 
(list 640.4638 868.2211) 
(list 640.4638 868.2314) 
(list 640.4638 868.2417) 
(list 640.4638 868.2519) 
(list 640.4638 868.2622) 
(list 640.4638 868.2725) 
(list 640.4638 868.2828) 
(list 640.4638 868.2931) 
(list 640.4638 868.3033) 
(list 640.4638 868.3136) 
(list 640.4638 868.3239) 
(list 640.4638 868.3342) 
(list 640.4638 868.3444) 
(list 640.4638 868.3547) 
(list 640.4638 868.365) 
(list 640.4638 868.3753) 
(list 640.4638 868.3856) 
(list 640.4638 868.3958) 
(list 640.4638 868.4061) 
(list 640.4638 868.4164) 
(list 640.4638 868.4267) 
(list 640.4638 868.4369) 
(list 640.4638 868.4472) 
(list 640.4638 868.4575) 
(list 640.4638 868.4678) 
(list 640.4638 868.4781) 
(list 640.4638 868.4883) 
(list 640.4638 868.4986) 
(list 640.4638 868.5089) 
(list 640.4638 868.5192) 
(list 640.4638 868.5294) 
(list 640.4638 868.5397) 
(list 640.4638 868.55) 
(list 641.123 868.55)))
(apply 'command (append '("pline") coords '("c")))
(setq tap2 (ssadd (entlast) tap2))
(command "_mirror" (entlast) "" "640,900" "640,901" "No")
(setq tap2 (ssadd (entlast) tap2))
(setq coords (list 
(list 640 868.55) 
(list 640.135 868.55) 
(list 640.135 868.5603) 
(list 640.135 868.5706) 
(list 640.135 868.5808) 
(list 640.135 868.5911) 
(list 640.135 868.6014) 
(list 640.135 868.6117) 
(list 640.135 868.6219) 
(list 640.135 868.6322) 
(list 640.135 868.6425) 
(list 640.135 868.6528) 
(list 640.135 868.6631) 
(list 640.135 868.6733) 
(list 640.135 868.6836) 
(list 640.135 868.6939) 
(list 640.135 868.7042) 
(list 640.135 868.7144) 
(list 640.135 868.7247) 
(list 640.135 868.735) 
(list 640.135 868.7453) 
(list 640.135 868.7556) 
(list 640.135 868.7658) 
(list 640.135 868.7761) 
(list 640.135 868.7864) 
(list 640.135 868.7967) 
(list 640.135 868.8069) 
(list 640.135 868.8172) 
(list 640.135 868.8275) 
(list 640.135 868.8378) 
(list 640.135 868.8481) 
(list 640.135 868.8583) 
(list 640.135 868.8686) 
(list 640.135 868.8789) 
(list 640.135 868.8892) 
(list 640.135 868.8994) 
(list 640.135 868.9097) 
(list 640.135 868.92) 
(list 640 868.92)))
(apply 'command (append '("pline") coords '("c")))
(setq tap2 (ssadd (entlast) tap2))
(command "_mirror" (entlast) "" "640,900" "640,901" "No")
(setq tap2 (ssadd (entlast) tap2))
(setq coords (list 
(list 640.4736 868.55) 
(list 640.4638 868.55) 
(list 640.4634 868.5603) 
(list 640.4616 868.5706) 
(list 640.4585 868.5808) 
(list 640.4542 868.5911) 
(list 640.4487 868.6014) 
(list 640.4423 868.6117) 
(list 640.4351 868.6219) 
(list 640.4273 868.6322) 
(list 640.4192 868.6425) 
(list 640.411 868.6528) 
(list 640.403 868.6631) 
(list 640.3954 868.6733) 
(list 640.3884 868.6836) 
(list 640.3823 868.6939) 
(list 640.3773 868.7042) 
(list 640.3735 868.7144) 
(list 640.3711 868.7247) 
(list 640.3701 868.735) 
(list 640.3706 868.7453) 
(list 640.3726 868.7556) 
(list 640.3761 868.7658) 
(list 640.3809 868.7761) 
(list 640.387 868.7864) 
(list 640.3941 868.7967) 
(list 640.4021 868.8069) 
(list 640.4107 868.8172) 
(list 640.4196 868.8275) 
(list 640.4286 868.8378) 
(list 640.4374 868.8481) 
(list 640.4458 868.8583) 
(list 640.4535 868.8686) 
(list 640.4602 868.8789) 
(list 640.4657 868.8892) 
(list 640.4698 868.8994) 
(list 640.4725 868.9097) 
(list 640.4736 868.92) 
(list 640.4736 868.92)))
(apply 'command (append '("pline") coords '("c")))
(setq tap2 (ssadd (entlast) tap2))
(command "_mirror" (entlast) "" "640,900" "640,901" "No")
(setq tap2 (ssadd (entlast) tap2))
(setq coords (list 
(list 641.123 868.55) 
(list 640.4736 868.55) 
(list 640.4736 868.5603) 
(list 640.4736 868.5706) 
(list 640.4736 868.5808) 
(list 640.4736 868.5911) 
(list 640.4736 868.6014) 
(list 640.4736 868.6117) 
(list 640.4736 868.6219) 
(list 640.4736 868.6322) 
(list 640.4736 868.6425) 
(list 640.4736 868.6528) 
(list 640.4736 868.6631) 
(list 640.4736 868.6733) 
(list 640.4736 868.6836) 
(list 640.4736 868.6939) 
(list 640.4736 868.7042) 
(list 640.4736 868.7144) 
(list 640.4736 868.7247) 
(list 640.4736 868.735) 
(list 640.4736 868.7453) 
(list 640.4736 868.7556) 
(list 640.4736 868.7658) 
(list 640.4736 868.7761) 
(list 640.4736 868.7864) 
(list 640.4736 868.7967) 
(list 640.4736 868.8069) 
(list 640.4736 868.8172) 
(list 640.4736 868.8275) 
(list 640.4736 868.8378) 
(list 640.4736 868.8481) 
(list 640.4736 868.8583) 
(list 640.4736 868.8686) 
(list 640.4736 868.8789) 
(list 640.4736 868.8892) 
(list 640.4736 868.8994) 
(list 640.4736 868.9097) 
(list 640.4736 868.92) 
(list 641.123 868.92)))
(apply 'command (append '("pline") coords '("c")))
(setq tap2 (ssadd (entlast) tap2))
(command "_mirror" (entlast) "" "640,900" "640,901" "No")
(setq tap2 (ssadd (entlast) tap2))
(setq coords (list 
(list 640 868.92) 
(list 640.135 868.92) 
(list 640.135 868.9303) 
(list 640.135 868.9406) 
(list 640.135 868.9508) 
(list 640.135 868.9611) 
(list 640.135 868.9714) 
(list 640.135 868.9817) 
(list 640.135 868.9919) 
(list 640.135 869.0022) 
(list 640.135 869.0125) 
(list 640.135 869.0228) 
(list 640.135 869.0331) 
(list 640.135 869.0433) 
(list 640.135 869.0536) 
(list 640.135 869.0639) 
(list 640.135 869.0742) 
(list 640.135 869.0844) 
(list 640.135 869.0947) 
(list 640.135 869.105) 
(list 640.135 869.1153) 
(list 640.135 869.1256) 
(list 640.135 869.1358) 
(list 640.135 869.1461) 
(list 640.135 869.1564) 
(list 640.135 869.1667) 
(list 640.135 869.1769) 
(list 640.135 869.1872) 
(list 640.135 869.1975) 
(list 640.135 869.2078) 
(list 640.135 869.2181) 
(list 640.135 869.2283) 
(list 640.135 869.2386) 
(list 640.135 869.2489) 
(list 640.135 869.2592) 
(list 640.135 869.2694) 
(list 640.135 869.2797) 
(list 640.135 869.29) 
(list 640 869.29)))
(apply 'command (append '("pline") coords '("c")))
(setq tap2 (ssadd (entlast) tap2))
(command "_mirror" (entlast) "" "640,900" "640,901" "No")
(setq tap2 (ssadd (entlast) tap2))
(setq coords (list 
(list 640.4834 868.92) 
(list 640.4736 868.92) 
(list 640.473 868.9303) 
(list 640.4709 868.9406) 
(list 640.4671 868.9508) 
(list 640.4619 868.9611) 
(list 640.4553 868.9714) 
(list 640.4476 868.9817) 
(list 640.439 868.9919) 
(list 640.4297 869.0022) 
(list 640.42 869.0125) 
(list 640.4102 869.0228) 
(list 640.4007 869.0331) 
(list 640.3917 869.0433) 
(list 640.3834 869.0536) 
(list 640.3762 869.0639) 
(list 640.3703 869.0742) 
(list 640.3659 869.0844) 
(list 640.363 869.0947) 
(list 640.3619 869.105) 
(list 640.3626 869.1153) 
(list 640.365 869.1256) 
(list 640.3691 869.1358) 
(list 640.3749 869.1461) 
(list 640.382 869.1564) 
(list 640.3904 869.1667) 
(list 640.3998 869.1769) 
(list 640.4099 869.1872) 
(list 640.4204 869.1975) 
(list 640.431 869.2078) 
(list 640.4413 869.2181) 
(list 640.4511 869.2283) 
(list 640.46 869.2386) 
(list 640.4678 869.2489) 
(list 640.4742 869.2592) 
(list 640.4791 869.2694) 
(list 640.4821 869.2797) 
(list 640.4834 869.29) 
(list 640.4834 869.29)))
(apply 'command (append '("pline") coords '("c")))
(setq tap2 (ssadd (entlast) tap2))
(command "_mirror" (entlast) "" "640,900" "640,901" "No")
(setq tap2 (ssadd (entlast) tap2))
(setq coords (list 
(list 641.123 868.92) 
(list 640.4834 868.92) 
(list 640.4834 868.9303) 
(list 640.4834 868.9406) 
(list 640.4834 868.9508) 
(list 640.4834 868.9611) 
(list 640.4834 868.9714) 
(list 640.4834 868.9817) 
(list 640.4834 868.9919) 
(list 640.4834 869.0022) 
(list 640.4834 869.0125) 
(list 640.4834 869.0228) 
(list 640.4834 869.0331) 
(list 640.4834 869.0433) 
(list 640.4834 869.0536) 
(list 640.4834 869.0639) 
(list 640.4834 869.0742) 
(list 640.4834 869.0844) 
(list 640.4834 869.0947) 
(list 640.4834 869.105) 
(list 640.4834 869.1153) 
(list 640.4834 869.1256) 
(list 640.4834 869.1358) 
(list 640.4834 869.1461) 
(list 640.4834 869.1564) 
(list 640.4834 869.1667) 
(list 640.4834 869.1769) 
(list 640.4834 869.1872) 
(list 640.4834 869.1975) 
(list 640.4834 869.2078) 
(list 640.4834 869.2181) 
(list 640.4834 869.2283) 
(list 640.4834 869.2386) 
(list 640.4834 869.2489) 
(list 640.4834 869.2592) 
(list 640.4834 869.2694) 
(list 640.4834 869.2797) 
(list 640.4834 869.29) 
(list 641.123 869.29)))
(apply 'command (append '("pline") coords '("c")))
(setq tap2 (ssadd (entlast) tap2))
(command "_mirror" (entlast) "" "640,900" "640,901" "No")
(setq tap2 (ssadd (entlast) tap2))
(setq coords (list 
(list 640 869.29) 
(list 640.135 869.29) 
(list 640.135 869.3003) 
(list 640.135 869.3106) 
(list 640.135 869.3208) 
(list 640.135 869.3311) 
(list 640.135 869.3414) 
(list 640.135 869.3517) 
(list 640.135 869.3619) 
(list 640.135 869.3722) 
(list 640.135 869.3825) 
(list 640.135 869.3928) 
(list 640.135 869.4031) 
(list 640.135 869.4133) 
(list 640.135 869.4236) 
(list 640.135 869.4339) 
(list 640.135 869.4442) 
(list 640.135 869.4544) 
(list 640.135 869.4647) 
(list 640.135 869.475) 
(list 640.135 869.4853) 
(list 640.135 869.4956) 
(list 640.135 869.5058) 
(list 640.135 869.5161) 
(list 640.135 869.5264) 
(list 640.135 869.5367) 
(list 640.135 869.5469) 
(list 640.135 869.5572) 
(list 640.135 869.5675) 
(list 640.135 869.5778) 
(list 640.135 869.5881) 
(list 640.135 869.5983) 
(list 640.135 869.6086) 
(list 640.135 869.6189) 
(list 640.135 869.6292) 
(list 640.135 869.6394) 
(list 640.135 869.6497) 
(list 640.135 869.66) 
(list 640 869.66)))
(apply 'command (append '("pline") coords '("c")))
(setq tap2 (ssadd (entlast) tap2))
(command "_mirror" (entlast) "" "640,900" "640,901" "No")
(setq tap2 (ssadd (entlast) tap2))
(setq coords (list 
(list 640.4931 869.29) 
(list 640.4834 869.29) 
(list 640.4827 869.3003) 
(list 640.4801 869.3106) 
(list 640.4757 869.3208) 
(list 640.4695 869.3311) 
(list 640.4619 869.3414) 
(list 640.4529 869.3517) 
(list 640.4428 869.3619) 
(list 640.432 869.3722) 
(list 640.4208 869.3825) 
(list 640.4095 869.3928) 
(list 640.3984 869.4031) 
(list 640.388 869.4133) 
(list 640.3785 869.4236) 
(list 640.3702 869.4339) 
(list 640.3633 869.4442) 
(list 640.3582 869.4544) 
(list 640.355 869.4647) 
(list 640.3537 869.475) 
(list 640.3545 869.4853) 
(list 640.3574 869.4956) 
(list 640.3622 869.5058) 
(list 640.3688 869.5161) 
(list 640.3771 869.5264) 
(list 640.3868 869.5367) 
(list 640.3976 869.5469) 
(list 640.4092 869.5572) 
(list 640.4212 869.5675) 
(list 640.4333 869.5778) 
(list 640.4452 869.5881) 
(list 640.4564 869.5983) 
(list 640.4666 869.6086) 
(list 640.4755 869.6189) 
(list 640.4828 869.6292) 
(list 640.4883 869.6394) 
(list 640.4918 869.6497) 
(list 640.4931 869.66) 
(list 640.4931 869.66)))
(apply 'command (append '("pline") coords '("c")))
(setq tap2 (ssadd (entlast) tap2))
(command "_mirror" (entlast) "" "640,900" "640,901" "No")
(setq tap2 (ssadd (entlast) tap2))
(setq coords (list 
(list 641.123 869.29) 
(list 640.4931 869.29) 
(list 640.4931 869.3003) 
(list 640.4931 869.3106) 
(list 640.4931 869.3208) 
(list 640.4931 869.3311) 
(list 640.4931 869.3414) 
(list 640.4931 869.3517) 
(list 640.4931 869.3619) 
(list 640.4931 869.3722) 
(list 640.4931 869.3825) 
(list 640.4931 869.3928) 
(list 640.4931 869.4031) 
(list 640.4931 869.4133) 
(list 640.4931 869.4236) 
(list 640.4931 869.4339) 
(list 640.4931 869.4442) 
(list 640.4931 869.4544) 
(list 640.4931 869.4647) 
(list 640.4931 869.475) 
(list 640.4931 869.4853) 
(list 640.4931 869.4956) 
(list 640.4931 869.5058) 
(list 640.4931 869.5161) 
(list 640.4931 869.5264) 
(list 640.4931 869.5367) 
(list 640.4931 869.5469) 
(list 640.4931 869.5572) 
(list 640.4931 869.5675) 
(list 640.4931 869.5778) 
(list 640.4931 869.5881) 
(list 640.4931 869.5983) 
(list 640.4931 869.6086) 
(list 640.4931 869.6189) 
(list 640.4931 869.6292) 
(list 640.4931 869.6394) 
(list 640.4931 869.6497) 
(list 640.4931 869.66) 
(list 641.123 869.66)))
(apply 'command (append '("pline") coords '("c")))
(setq tap2 (ssadd (entlast) tap2))
(command "_mirror" (entlast) "" "640,900" "640,901" "No")
(setq tap2 (ssadd (entlast) tap2))
(setq coords (list 
(list 640 869.66) 
(list 640.135 869.66) 
(list 640.135 869.6703) 
(list 640.135 869.6806) 
(list 640.135 869.6908) 
(list 640.135 869.7011) 
(list 640.135 869.7114) 
(list 640.135 869.7217) 
(list 640.135 869.7319) 
(list 640.135 869.7422) 
(list 640.135 869.7525) 
(list 640.135 869.7628) 
(list 640.135 869.7731) 
(list 640.135 869.7833) 
(list 640.135 869.7936) 
(list 640.135 869.8039) 
(list 640.135 869.8142) 
(list 640.135 869.8244) 
(list 640.135 869.8347) 
(list 640.135 869.845) 
(list 640.135 869.8553) 
(list 640.135 869.8656) 
(list 640.135 869.8758) 
(list 640.135 869.8861) 
(list 640.135 869.8964) 
(list 640.135 869.9067) 
(list 640.135 869.9169) 
(list 640.135 869.9272) 
(list 640.135 869.9375) 
(list 640.135 869.9478) 
(list 640.135 869.9581) 
(list 640.135 869.9683) 
(list 640.135 869.9786) 
(list 640.135 869.9889) 
(list 640.135 869.9992) 
(list 640.135 870.0094) 
(list 640.135 870.0197) 
(list 640.135 870.03) 
(list 640 870.03)))
(apply 'command (append '("pline") coords '("c")))
(setq tap2 (ssadd (entlast) tap2))
(command "_mirror" (entlast) "" "640,900" "640,901" "No")
(setq tap2 (ssadd (entlast) tap2))
(setq coords (list 
(list 640.5029 869.66) 
(list 640.4931 869.66) 
(list 640.4923 869.6703) 
(list 640.4893 869.6806) 
(list 640.4842 869.6908) 
(list 640.4772 869.7011) 
(list 640.4684 869.7114) 
(list 640.4581 869.7217) 
(list 640.4467 869.7319) 
(list 640.4344 869.7422) 
(list 640.4216 869.7525) 
(list 640.4087 869.7628) 
(list 640.3962 869.7731) 
(list 640.3843 869.7833) 
(list 640.3735 869.7936) 
(list 640.3641 869.8039) 
(list 640.3564 869.8142) 
(list 640.3506 869.8244) 
(list 640.347 869.8347) 
(list 640.3456 869.845) 
(list 640.3465 869.8553) 
(list 640.3498 869.8656) 
(list 640.3552 869.8758) 
(list 640.3627 869.8861) 
(list 640.3721 869.8964) 
(list 640.3831 869.9067) 
(list 640.3953 869.9169) 
(list 640.4084 869.9272) 
(list 640.422 869.9375) 
(list 640.4357 869.9478) 
(list 640.449 869.9581) 
(list 640.4617 869.9683) 
(list 640.4732 869.9786) 
(list 640.4832 869.9889) 
(list 640.4914 869.9992) 
(list 640.4975 870.0094) 
(list 640.5014 870.0197) 
(list 640.5029 870.03) 
(list 640.5029 870.03)))
(apply 'command (append '("pline") coords '("c")))
(setq tap2 (ssadd (entlast) tap2))
(command "_mirror" (entlast) "" "640,900" "640,901" "No")
(setq tap2 (ssadd (entlast) tap2))
(setq coords (list 
(list 641.123 869.66) 
(list 640.5029 869.66) 
(list 640.5029 869.6703) 
(list 640.5029 869.6806) 
(list 640.5029 869.6908) 
(list 640.5029 869.7011) 
(list 640.5029 869.7114) 
(list 640.5029 869.7217) 
(list 640.5029 869.7319) 
(list 640.5029 869.7422) 
(list 640.5029 869.7525) 
(list 640.5029 869.7628) 
(list 640.5029 869.7731) 
(list 640.5029 869.7833) 
(list 640.5029 869.7936) 
(list 640.5029 869.8039) 
(list 640.5029 869.8142) 
(list 640.5029 869.8244) 
(list 640.5029 869.8347) 
(list 640.5029 869.845) 
(list 640.5029 869.8553) 
(list 640.5029 869.8656) 
(list 640.5029 869.8758) 
(list 640.5029 869.8861) 
(list 640.5029 869.8964) 
(list 640.5029 869.9067) 
(list 640.5029 869.9169) 
(list 640.5029 869.9272) 
(list 640.5029 869.9375) 
(list 640.5029 869.9478) 
(list 640.5029 869.9581) 
(list 640.5029 869.9683) 
(list 640.5029 869.9786) 
(list 640.5029 869.9889) 
(list 640.5029 869.9992) 
(list 640.5029 870.0094) 
(list 640.5029 870.0197) 
(list 640.5029 870.03) 
(list 641.123 870.03)))
(apply 'command (append '("pline") coords '("c")))
(setq tap2 (ssadd (entlast) tap2))
(command "_mirror" (entlast) "" "640,900" "640,901" "No")
(setq tap2 (ssadd (entlast) tap2))
(setq coords (list 
(list 640 870.03) 
(list 640.135 870.03) 
(list 640.135 870.0403) 
(list 640.135 870.0506) 
(list 640.135 870.0608) 
(list 640.135 870.0711) 
(list 640.135 870.0814) 
(list 640.135 870.0917) 
(list 640.135 870.1019) 
(list 640.135 870.1122) 
(list 640.135 870.1225) 
(list 640.135 870.1328) 
(list 640.135 870.1431) 
(list 640.135 870.1533) 
(list 640.135 870.1636) 
(list 640.135 870.1739) 
(list 640.135 870.1842) 
(list 640.135 870.1944) 
(list 640.135 870.2047) 
(list 640.135 870.215) 
(list 640.135 870.2253) 
(list 640.135 870.2356) 
(list 640.135 870.2458) 
(list 640.135 870.2561) 
(list 640.135 870.2664) 
(list 640.135 870.2767) 
(list 640.135 870.2869) 
(list 640.135 870.2972) 
(list 640.135 870.3075) 
(list 640.135 870.3178) 
(list 640.135 870.3281) 
(list 640.135 870.3383) 
(list 640.135 870.3486) 
(list 640.135 870.3589) 
(list 640.135 870.3692) 
(list 640.135 870.3794) 
(list 640.135 870.3897) 
(list 640.135 870.4) 
(list 640 870.4)))
(apply 'command (append '("pline") coords '("c")))
(setq tap2 (ssadd (entlast) tap2))
(command "_mirror" (entlast) "" "640,900" "640,901" "No")
(setq tap2 (ssadd (entlast) tap2))
(setq coords (list 
(list 640.5127 870.03) 
(list 640.5029 870.03) 
(list 640.5019 870.0403) 
(list 640.4985 870.0506) 
(list 640.4928 870.0608) 
(list 640.4849 870.0711) 
(list 640.475 870.0814) 
(list 640.4634 870.0917) 
(list 640.4506 870.1019) 
(list 640.4367 870.1122) 
(list 640.4224 870.1225) 
(list 640.408 870.1328) 
(list 640.3939 870.1431) 
(list 640.3806 870.1533) 
(list 640.3685 870.1636) 
(list 640.358 870.1739) 
(list 640.3494 870.1842) 
(list 640.343 870.1944) 
(list 640.3389 870.2047) 
(list 640.3374 870.215) 
(list 640.3385 870.2253) 
(list 640.3421 870.2356) 
(list 640.3482 870.2458) 
(list 640.3567 870.2561) 
(list 640.3672 870.2664) 
(list 640.3794 870.2767) 
(list 640.393 870.2869) 
(list 640.4076 870.2972) 
(list 640.4228 870.3075) 
(list 640.438 870.3178) 
(list 640.4529 870.3281) 
(list 640.467 870.3383) 
(list 640.4797 870.3486) 
(list 640.4908 870.3589) 
(list 640.4999 870.3692) 
(list 640.5067 870.3794) 
(list 640.511 870.3897) 
(list 640.5127 870.4) 
(list 640.5127 870.4)))
(apply 'command (append '("pline") coords '("c")))
(setq tap2 (ssadd (entlast) tap2))
(command "_mirror" (entlast) "" "640,900" "640,901" "No")
(setq tap2 (ssadd (entlast) tap2))
(setq coords (list 
(list 641.123 870.03) 
(list 640.5127 870.03) 
(list 640.5127 870.0403) 
(list 640.5127 870.0506) 
(list 640.5127 870.0608) 
(list 640.5127 870.0711) 
(list 640.5127 870.0814) 
(list 640.5127 870.0917) 
(list 640.5127 870.1019) 
(list 640.5127 870.1122) 
(list 640.5127 870.1225) 
(list 640.5127 870.1328) 
(list 640.5127 870.1431) 
(list 640.5127 870.1533) 
(list 640.5127 870.1636) 
(list 640.5127 870.1739) 
(list 640.5127 870.1842) 
(list 640.5127 870.1944) 
(list 640.5127 870.2047) 
(list 640.5127 870.215) 
(list 640.5127 870.2253) 
(list 640.5127 870.2356) 
(list 640.5127 870.2458) 
(list 640.5127 870.2561) 
(list 640.5127 870.2664) 
(list 640.5127 870.2767) 
(list 640.5127 870.2869) 
(list 640.5127 870.2972) 
(list 640.5127 870.3075) 
(list 640.5127 870.3178) 
(list 640.5127 870.3281) 
(list 640.5127 870.3383) 
(list 640.5127 870.3486) 
(list 640.5127 870.3589) 
(list 640.5127 870.3692) 
(list 640.5127 870.3794) 
(list 640.5127 870.3897) 
(list 640.5127 870.4) 
(list 641.123 870.4)))
(apply 'command (append '("pline") coords '("c")))
(setq tap2 (ssadd (entlast) tap2))
(command "_mirror" (entlast) "" "640,900" "640,901" "No")
(setq tap2 (ssadd (entlast) tap2))
(setq coords (list 
(list 640 870.4) 
(list 640.135 870.4) 
(list 640.135 870.4103) 
(list 640.135 870.4206) 
(list 640.135 870.4308) 
(list 640.135 870.4411) 
(list 640.135 870.4514) 
(list 640.135 870.4617) 
(list 640.135 870.4719) 
(list 640.135 870.4822) 
(list 640.135 870.4925) 
(list 640.135 870.5028) 
(list 640.135 870.5131) 
(list 640.135 870.5233) 
(list 640.135 870.5336) 
(list 640.135 870.5439) 
(list 640.135 870.5542) 
(list 640.135 870.5644) 
(list 640.135 870.5747) 
(list 640.135 870.585) 
(list 640.135 870.5953) 
(list 640.135 870.6056) 
(list 640.135 870.6158) 
(list 640.135 870.6261) 
(list 640.135 870.6364) 
(list 640.135 870.6467) 
(list 640.135 870.6569) 
(list 640.135 870.6672) 
(list 640.135 870.6775) 
(list 640.135 870.6878) 
(list 640.135 870.6981) 
(list 640.135 870.7083) 
(list 640.135 870.7186) 
(list 640.135 870.7289) 
(list 640.135 870.7392) 
(list 640.135 870.7494) 
(list 640.135 870.7597) 
(list 640.135 870.77) 
(list 640 870.77)))
(apply 'command (append '("pline") coords '("c")))
(setq tap2 (ssadd (entlast) tap2))
(command "_mirror" (entlast) "" "640,900" "640,901" "No")
(setq tap2 (ssadd (entlast) tap2))
(setq coords (list 
(list 640.5224 870.4) 
(list 640.5127 870.4) 
(list 640.5116 870.4103) 
(list 640.5078 870.4206) 
(list 640.5014 870.4308) 
(list 640.4925 870.4411) 
(list 640.4815 870.4514) 
(list 640.4687 870.4617) 
(list 640.4544 870.4719) 
(list 640.4391 870.4822) 
(list 640.4232 870.4925) 
(list 640.4072 870.5028) 
(list 640.3916 870.5131) 
(list 640.3769 870.5233) 
(list 640.3636 870.5336) 
(list 640.352 870.5439) 
(list 640.3424 870.5542) 
(list 640.3354 870.5644) 
(list 640.3309 870.5747) 
(list 640.3293 870.585) 
(list 640.3305 870.5953) 
(list 640.3345 870.6056) 
(list 640.3413 870.6158) 
(list 640.3506 870.6261) 
(list 640.3622 870.6364) 
(list 640.3757 870.6467) 
(list 640.3908 870.6569) 
(list 640.4069 870.6672) 
(list 640.4236 870.6775) 
(list 640.4404 870.6878) 
(list 640.4568 870.6981) 
(list 640.4722 870.7083) 
(list 640.4863 870.7186) 
(list 640.4985 870.7289) 
(list 640.5085 870.7392) 
(list 640.516 870.7494) 
(list 640.5207 870.7597) 
(list 640.5224 870.77) 
(list 640.5224 870.77)))
(apply 'command (append '("pline") coords '("c")))
(setq tap2 (ssadd (entlast) tap2))
(command "_mirror" (entlast) "" "640,900" "640,901" "No")
(setq tap2 (ssadd (entlast) tap2))
(setq coords (list 
(list 641.123 870.4) 
(list 640.5224 870.4) 
(list 640.5224 870.4103) 
(list 640.5224 870.4206) 
(list 640.5224 870.4308) 
(list 640.5224 870.4411) 
(list 640.5224 870.4514) 
(list 640.5224 870.4617) 
(list 640.5224 870.4719) 
(list 640.5224 870.4822) 
(list 640.5224 870.4925) 
(list 640.5224 870.5028) 
(list 640.5224 870.5131) 
(list 640.5224 870.5233) 
(list 640.5224 870.5336) 
(list 640.5224 870.5439) 
(list 640.5224 870.5542) 
(list 640.5224 870.5644) 
(list 640.5224 870.5747) 
(list 640.5224 870.585) 
(list 640.5224 870.5953) 
(list 640.5224 870.6056) 
(list 640.5224 870.6158) 
(list 640.5224 870.6261) 
(list 640.5224 870.6364) 
(list 640.5224 870.6467) 
(list 640.5224 870.6569) 
(list 640.5224 870.6672) 
(list 640.5224 870.6775) 
(list 640.5224 870.6878) 
(list 640.5224 870.6981) 
(list 640.5224 870.7083) 
(list 640.5224 870.7186) 
(list 640.5224 870.7289) 
(list 640.5224 870.7392) 
(list 640.5224 870.7494) 
(list 640.5224 870.7597) 
(list 640.5224 870.77) 
(list 641.123 870.77)))
(apply 'command (append '("pline") coords '("c")))
(setq tap2 (ssadd (entlast) tap2))
(command "_mirror" (entlast) "" "640,900" "640,901" "No")
(setq tap2 (ssadd (entlast) tap2))
(setq coords (list 
(list 640 870.77) 
(list 640.135 870.77) 
(list 640.135 870.7803) 
(list 640.135 870.7906) 
(list 640.135 870.8008) 
(list 640.135 870.8111) 
(list 640.135 870.8214) 
(list 640.135 870.8317) 
(list 640.135 870.8419) 
(list 640.135 870.8522) 
(list 640.135 870.8625) 
(list 640.135 870.8728) 
(list 640.135 870.8831) 
(list 640.135 870.8933) 
(list 640.135 870.9036) 
(list 640.135 870.9139) 
(list 640.135 870.9242) 
(list 640.135 870.9344) 
(list 640.135 870.9447) 
(list 640.135 870.955) 
(list 640.135 870.9653) 
(list 640.135 870.9756) 
(list 640.135 870.9858) 
(list 640.135 870.9961) 
(list 640.135 871.0064) 
(list 640.135 871.0167) 
(list 640.135 871.0269) 
(list 640.135 871.0372) 
(list 640.135 871.0475) 
(list 640.135 871.0578) 
(list 640.135 871.0681) 
(list 640.135 871.0783) 
(list 640.135 871.0886) 
(list 640.135 871.0989) 
(list 640.135 871.1092) 
(list 640.135 871.1194) 
(list 640.135 871.1297) 
(list 640.135 871.14) 
(list 640 871.14)))
(apply 'command (append '("pline") coords '("c")))
(setq tap2 (ssadd (entlast) tap2))
(command "_mirror" (entlast) "" "640,900" "640,901" "No")
(setq tap2 (ssadd (entlast) tap2))
(setq coords (list 
(list 640.5322 870.77) 
(list 640.5224 870.77) 
(list 640.5212 870.7803) 
(list 640.517 870.7906) 
(list 640.5099 870.8008) 
(list 640.5002 870.8111) 
(list 640.4881 870.8214) 
(list 640.474 870.8317) 
(list 640.4583 870.8419) 
(list 640.4415 870.8522) 
(list 640.424 870.8625) 
(list 640.4065 870.8728) 
(list 640.3894 870.8831) 
(list 640.3733 870.8933) 
(list 640.3586 870.9036) 
(list 640.3459 870.9139) 
(list 640.3355 870.9242) 
(list 640.3277 870.9344) 
(list 640.3229 870.9447) 
(list 640.3211 870.955) 
(list 640.3224 870.9653) 
(list 640.3269 870.9756) 
(list 640.3343 870.9858) 
(list 640.3445 870.9961) 
(list 640.3572 871.0064) 
(list 640.372 871.0167) 
(list 640.3885 871.0269) 
(list 640.4061 871.0372) 
(list 640.4244 871.0475) 
(list 640.4428 871.0578) 
(list 640.4606 871.0681) 
(list 640.4775 871.0783) 
(list 640.4929 871.0886) 
(list 640.5062 871.0989) 
(list 640.5171 871.1092) 
(list 640.5252 871.1194) 
(list 640.5303 871.1297) 
(list 640.5322 871.14) 
(list 640.5322 871.14)))
(apply 'command (append '("pline") coords '("c")))
(setq tap2 (ssadd (entlast) tap2))
(command "_mirror" (entlast) "" "640,900" "640,901" "No")
(setq tap2 (ssadd (entlast) tap2))
(setq coords (list 
(list 641.123 870.77) 
(list 640.5322 870.77) 
(list 640.5322 870.7803) 
(list 640.5322 870.7906) 
(list 640.5322 870.8008) 
(list 640.5322 870.8111) 
(list 640.5322 870.8214) 
(list 640.5322 870.8317) 
(list 640.5322 870.8419) 
(list 640.5322 870.8522) 
(list 640.5322 870.8625) 
(list 640.5322 870.8728) 
(list 640.5322 870.8831) 
(list 640.5322 870.8933) 
(list 640.5322 870.9036) 
(list 640.5322 870.9139) 
(list 640.5322 870.9242) 
(list 640.5322 870.9344) 
(list 640.5322 870.9447) 
(list 640.5322 870.955) 
(list 640.5322 870.9653) 
(list 640.5322 870.9756) 
(list 640.5322 870.9858) 
(list 640.5322 870.9961) 
(list 640.5322 871.0064) 
(list 640.5322 871.0167) 
(list 640.5322 871.0269) 
(list 640.5322 871.0372) 
(list 640.5322 871.0475) 
(list 640.5322 871.0578) 
(list 640.5322 871.0681) 
(list 640.5322 871.0783) 
(list 640.5322 871.0886) 
(list 640.5322 871.0989) 
(list 640.5322 871.1092) 
(list 640.5322 871.1194) 
(list 640.5322 871.1297) 
(list 640.5322 871.14) 
(list 641.123 871.14)))
(apply 'command (append '("pline") coords '("c")))
(setq tap2 (ssadd (entlast) tap2))
(command "_mirror" (entlast) "" "640,900" "640,901" "No")
(setq tap2 (ssadd (entlast) tap2))
(setq coords (list 
(list 640 871.14) 
(list 640.135 871.14) 
(list 640.135 871.1503) 
(list 640.135 871.1606) 
(list 640.135 871.1708) 
(list 640.135 871.1811) 
(list 640.135 871.1914) 
(list 640.135 871.2017) 
(list 640.135 871.2119) 
(list 640.135 871.2222) 
(list 640.135 871.2325) 
(list 640.135 871.2428) 
(list 640.135 871.2531) 
(list 640.135 871.2633) 
(list 640.135 871.2736) 
(list 640.135 871.2839) 
(list 640.135 871.2942) 
(list 640.135 871.3044) 
(list 640.135 871.3147) 
(list 640.135 871.325) 
(list 640.135 871.3353) 
(list 640.135 871.3456) 
(list 640.135 871.3558) 
(list 640.135 871.3661) 
(list 640.135 871.3764) 
(list 640.135 871.3867) 
(list 640.135 871.3969) 
(list 640.135 871.4072) 
(list 640.135 871.4175) 
(list 640.135 871.4278) 
(list 640.135 871.4381) 
(list 640.135 871.4483) 
(list 640.135 871.4586) 
(list 640.135 871.4689) 
(list 640.135 871.4792) 
(list 640.135 871.4894) 
(list 640.135 871.4997) 
(list 640.135 871.51) 
(list 640 871.51)))
(apply 'command (append '("pline") coords '("c")))
(setq tap2 (ssadd (entlast) tap2))
(command "_mirror" (entlast) "" "640,900" "640,901" "No")
(setq tap2 (ssadd (entlast) tap2))
(setq coords (list 
(list 640.542 871.14) 
(list 640.5322 871.14) 
(list 640.5308 871.1503) 
(list 640.5262 871.1606) 
(list 640.5185 871.1708) 
(list 640.5079 871.1811) 
(list 640.4947 871.1914) 
(list 640.4793 871.2017) 
(list 640.4622 871.2119) 
(list 640.4438 871.2222) 
(list 640.4248 871.2325) 
(list 640.4057 871.2428) 
(list 640.3871 871.2531) 
(list 640.3696 871.2633) 
(list 640.3536 871.2736) 
(list 640.3398 871.2839) 
(list 640.3285 871.2942) 
(list 640.3201 871.3044) 
(list 640.3148 871.3147) 
(list 640.3129 871.325) 
(list 640.3144 871.3353) 
(list 640.3193 871.3456) 
(list 640.3274 871.3558) 
(list 640.3385 871.3661) 
(list 640.3523 871.3764) 
(list 640.3683 871.3867) 
(list 640.3862 871.3969) 
(list 640.4054 871.4072) 
(list 640.4252 871.4175) 
(list 640.4451 871.4278) 
(list 640.4645 871.4381) 
(list 640.4828 871.4483) 
(list 640.4994 871.4586) 
(list 640.5138 871.4689) 
(list 640.5256 871.4792) 
(list 640.5344 871.4894) 
(list 640.5399 871.4997) 
(list 640.542 871.51) 
(list 640.542 871.51)))
(apply 'command (append '("pline") coords '("c")))
(setq tap2 (ssadd (entlast) tap2))
(command "_mirror" (entlast) "" "640,900" "640,901" "No")
(setq tap2 (ssadd (entlast) tap2))
(setq coords (list 
(list 641.123 871.14) 
(list 640.542 871.14) 
(list 640.542 871.1503) 
(list 640.542 871.1606) 
(list 640.542 871.1708) 
(list 640.542 871.1811) 
(list 640.542 871.1914) 
(list 640.542 871.2017) 
(list 640.542 871.2119) 
(list 640.542 871.2222) 
(list 640.542 871.2325) 
(list 640.542 871.2428) 
(list 640.542 871.2531) 
(list 640.542 871.2633) 
(list 640.542 871.2736) 
(list 640.542 871.2839) 
(list 640.542 871.2942) 
(list 640.542 871.3044) 
(list 640.542 871.3147) 
(list 640.542 871.325) 
(list 640.542 871.3353) 
(list 640.542 871.3456) 
(list 640.542 871.3558) 
(list 640.542 871.3661) 
(list 640.542 871.3764) 
(list 640.542 871.3867) 
(list 640.542 871.3969) 
(list 640.542 871.4072) 
(list 640.542 871.4175) 
(list 640.542 871.4278) 
(list 640.542 871.4381) 
(list 640.542 871.4483) 
(list 640.542 871.4586) 
(list 640.542 871.4689) 
(list 640.542 871.4792) 
(list 640.542 871.4894) 
(list 640.542 871.4997) 
(list 640.542 871.51) 
(list 641.123 871.51)))
(apply 'command (append '("pline") coords '("c")))
(setq tap2 (ssadd (entlast) tap2))
(command "_mirror" (entlast) "" "640,900" "640,901" "No")
(setq tap2 (ssadd (entlast) tap2))
(setq coords (list 
(list 640 871.51) 
(list 640.135 871.51) 
(list 640.135 871.5203) 
(list 640.135 871.5306) 
(list 640.135 871.5408) 
(list 640.135 871.5511) 
(list 640.135 871.5614) 
(list 640.135 871.5717) 
(list 640.135 871.5819) 
(list 640.135 871.5922) 
(list 640.135 871.6025) 
(list 640.135 871.6128) 
(list 640.135 871.6231) 
(list 640.135 871.6333) 
(list 640.135 871.6436) 
(list 640.135 871.6539) 
(list 640.135 871.6642) 
(list 640.135 871.6744) 
(list 640.135 871.6847) 
(list 640.135 871.695) 
(list 640.135 871.7053) 
(list 640.135 871.7156) 
(list 640.135 871.7258) 
(list 640.135 871.7361) 
(list 640.135 871.7464) 
(list 640.135 871.7567) 
(list 640.135 871.7669) 
(list 640.135 871.7772) 
(list 640.135 871.7875) 
(list 640.135 871.7978) 
(list 640.135 871.8081) 
(list 640.135 871.8183) 
(list 640.135 871.8286) 
(list 640.135 871.8389) 
(list 640.135 871.8492) 
(list 640.135 871.8594) 
(list 640.135 871.8697) 
(list 640.135 871.88) 
(list 640 871.88)))
(apply 'command (append '("pline") coords '("c")))
(setq tap2 (ssadd (entlast) tap2))
(command "_mirror" (entlast) "" "640,900" "640,901" "No")
(setq tap2 (ssadd (entlast) tap2))
(setq coords (list 
(list 640.5517 871.51) 
(list 640.542 871.51) 
(list 640.5405 871.5203) 
(list 640.5354 871.5306) 
(list 640.5271 871.5408) 
(list 640.5155 871.5511) 
(list 640.5012 871.5614) 
(list 640.4846 871.5717) 
(list 640.466 871.5819) 
(list 640.4462 871.5922) 
(list 640.4256 871.6025) 
(list 640.4049 871.6128) 
(list 640.3848 871.6231) 
(list 640.3659 871.6333) 
(list 640.3487 871.6436) 
(list 640.3337 871.6539) 
(list 640.3215 871.6642) 
(list 640.3125 871.6744) 
(list 640.3068 871.6847) 
(list 640.3048 871.695) 
(list 640.3064 871.7053) 
(list 640.3116 871.7156) 
(list 640.3204 871.7258) 
(list 640.3324 871.7361) 
(list 640.3473 871.7464) 
(list 640.3647 871.7567) 
(list 640.384 871.7669) 
(list 640.4046 871.7772) 
(list 640.426 871.7875) 
(list 640.4475 871.7978) 
(list 640.4684 871.8081) 
(list 640.4881 871.8183) 
(list 640.506 871.8286) 
(list 640.5215 871.8389) 
(list 640.5342 871.8492) 
(list 640.5437 871.8594) 
(list 640.5496 871.8697) 
(list 640.5517 871.88) 
(list 640.5517 871.88)))
(apply 'command (append '("pline") coords '("c")))
(setq tap2 (ssadd (entlast) tap2))
(command "_mirror" (entlast) "" "640,900" "640,901" "No")
(setq tap2 (ssadd (entlast) tap2))
(setq coords (list 
(list 641.123 871.51) 
(list 640.5517 871.51) 
(list 640.5517 871.5203) 
(list 640.5517 871.5306) 
(list 640.5517 871.5408) 
(list 640.5517 871.5511) 
(list 640.5517 871.5614) 
(list 640.5517 871.5717) 
(list 640.5517 871.5819) 
(list 640.5517 871.5922) 
(list 640.5517 871.6025) 
(list 640.5517 871.6128) 
(list 640.5517 871.6231) 
(list 640.5517 871.6333) 
(list 640.5517 871.6436) 
(list 640.5517 871.6539) 
(list 640.5517 871.6642) 
(list 640.5517 871.6744) 
(list 640.5517 871.6847) 
(list 640.5517 871.695) 
(list 640.5517 871.7053) 
(list 640.5517 871.7156) 
(list 640.5517 871.7258) 
(list 640.5517 871.7361) 
(list 640.5517 871.7464) 
(list 640.5517 871.7567) 
(list 640.5517 871.7669) 
(list 640.5517 871.7772) 
(list 640.5517 871.7875) 
(list 640.5517 871.7978) 
(list 640.5517 871.8081) 
(list 640.5517 871.8183) 
(list 640.5517 871.8286) 
(list 640.5517 871.8389) 
(list 640.5517 871.8492) 
(list 640.5517 871.8594) 
(list 640.5517 871.8697) 
(list 640.5517 871.88) 
(list 641.123 871.88)))
(apply 'command (append '("pline") coords '("c")))
(setq tap2 (ssadd (entlast) tap2))
(command "_mirror" (entlast) "" "640,900" "640,901" "No")
(setq tap2 (ssadd (entlast) tap2))
(setq coords (list 
(list 640 871.88) 
(list 640.135 871.88) 
(list 640.135 871.8903) 
(list 640.135 871.9006) 
(list 640.135 871.9108) 
(list 640.135 871.9211) 
(list 640.135 871.9314) 
(list 640.135 871.9417) 
(list 640.135 871.9519) 
(list 640.135 871.9622) 
(list 640.135 871.9725) 
(list 640.135 871.9828) 
(list 640.135 871.9931) 
(list 640.135 872.0033) 
(list 640.135 872.0136) 
(list 640.135 872.0239) 
(list 640.135 872.0342) 
(list 640.135 872.0444) 
(list 640.135 872.0547) 
(list 640.135 872.065) 
(list 640.135 872.0753) 
(list 640.135 872.0856) 
(list 640.135 872.0958) 
(list 640.135 872.1061) 
(list 640.135 872.1164) 
(list 640.135 872.1267) 
(list 640.135 872.1369) 
(list 640.135 872.1472) 
(list 640.135 872.1575) 
(list 640.135 872.1678) 
(list 640.135 872.1781) 
(list 640.135 872.1883) 
(list 640.135 872.1986) 
(list 640.135 872.2089) 
(list 640.135 872.2192) 
(list 640.135 872.2294) 
(list 640.135 872.2397) 
(list 640.135 872.25) 
(list 640 872.25)))
(apply 'command (append '("pline") coords '("c")))
(setq tap2 (ssadd (entlast) tap2))
(command "_mirror" (entlast) "" "640,900" "640,901" "No")
(setq tap2 (ssadd (entlast) tap2))
(setq coords (list 
(list 640.5615 871.88) 
(list 640.5517 871.88) 
(list 640.5501 871.8903) 
(list 640.5447 871.9006) 
(list 640.5356 871.9108) 
(list 640.5232 871.9211) 
(list 640.5078 871.9314) 
(list 640.4898 871.9417) 
(list 640.4699 871.9519) 
(list 640.4485 871.9622) 
(list 640.4264 871.9725) 
(list 640.4042 871.9828) 
(list 640.3826 871.9931) 
(list 640.3622 872.0033) 
(list 640.3437 872.0136) 
(list 640.3277 872.0239) 
(list 640.3146 872.0342) 
(list 640.3048 872.0444) 
(list 640.2988 872.0547) 
(list 640.2966 872.065) 
(list 640.2983 872.0753) 
(list 640.304 872.0856) 
(list 640.3134 872.0958) 
(list 640.3263 872.1061) 
(list 640.3423 872.1164) 
(list 640.361 872.1267) 
(list 640.3817 872.1369) 
(list 640.4039 872.1472) 
(list 640.4268 872.1575) 
(list 640.4498 872.1678) 
(list 640.4723 872.1781) 
(list 640.4934 872.1883) 
(list 640.5125 872.1986) 
(list 640.5292 872.2089) 
(list 640.5428 872.2192) 
(list 640.5529 872.2294) 
(list 640.5592 872.2397) 
(list 640.5615 872.25) 
(list 640.5615 872.25)))
(apply 'command (append '("pline") coords '("c")))
(setq tap2 (ssadd (entlast) tap2))
(command "_mirror" (entlast) "" "640,900" "640,901" "No")
(setq tap2 (ssadd (entlast) tap2))
(setq coords (list 
(list 641.123 871.88) 
(list 640.5615 871.88) 
(list 640.5615 871.8903) 
(list 640.5615 871.9006) 
(list 640.5615 871.9108) 
(list 640.5615 871.9211) 
(list 640.5615 871.9314) 
(list 640.5615 871.9417) 
(list 640.5615 871.9519) 
(list 640.5615 871.9622) 
(list 640.5615 871.9725) 
(list 640.5615 871.9828) 
(list 640.5615 871.9931) 
(list 640.5615 872.0033) 
(list 640.5615 872.0136) 
(list 640.5615 872.0239) 
(list 640.5615 872.0342) 
(list 640.5615 872.0444) 
(list 640.5615 872.0547) 
(list 640.5615 872.065) 
(list 640.5615 872.0753) 
(list 640.5615 872.0856) 
(list 640.5615 872.0958) 
(list 640.5615 872.1061) 
(list 640.5615 872.1164) 
(list 640.5615 872.1267) 
(list 640.5615 872.1369) 
(list 640.5615 872.1472) 
(list 640.5615 872.1575) 
(list 640.5615 872.1678) 
(list 640.5615 872.1781) 
(list 640.5615 872.1883) 
(list 640.5615 872.1986) 
(list 640.5615 872.2089) 
(list 640.5615 872.2192) 
(list 640.5615 872.2294) 
(list 640.5615 872.2397) 
(list 640.5615 872.25) 
(list 641.123 872.25)))
(apply 'command (append '("pline") coords '("c")))
(setq tap2 (ssadd (entlast) tap2))
(command "_mirror" (entlast) "" "640,900" "640,901" "No")
(setq tap2 (ssadd (entlast) tap2))
(command "_block" "blktap2" "640,900" tap2 "")
(command "_insert" "blktap2" "640,900" "1" "1" "0")
(command "_insert" "blktap2" "640,900" "1" "1" "180")
(setq uc2 nil)
(setq uc2 (ssadd))
(setq coords (list 
(list 0 -0.185) 
(list 0.135 -0.185) 
(list 0.135 -0.17472) 
(list 0.135 -0.16444) 
(list 0.135 -0.15417) 
(list 0.135 -0.14389) 
(list 0.135 -0.13361) 
(list 0.135 -0.12333) 
(list 0.135 -0.11306) 
(list 0.135 -0.10278) 
(list 0.135 -0.0925) 
(list 0.135 -0.082222) 
(list 0.135 -0.071944) 
(list 0.135 -0.061667) 
(list 0.135 -0.051389) 
(list 0.135 -0.041111) 
(list 0.135 -0.030833) 
(list 0.135 -0.020556) 
(list 0.135 -0.010278) 
(list 0.135 0) 
(list 0.135 0.010278) 
(list 0.135 0.020556) 
(list 0.135 0.030833) 
(list 0.135 0.041111) 
(list 0.135 0.051389) 
(list 0.135 0.061667) 
(list 0.135 0.071944) 
(list 0.135 0.082222) 
(list 0.135 0.0925) 
(list 0.135 0.10278) 
(list 0.135 0.11306) 
(list 0.135 0.12333) 
(list 0.135 0.13361) 
(list 0.135 0.14389) 
(list 0.135 0.15417) 
(list 0.135 0.16444) 
(list 0.135 0.17472) 
(list 0.135 0.185) 
(list 0 0.185)))
(apply 'command (append '("pline") coords '("c")))
(setq uc2 (ssadd (entlast) uc2))
(setq coords (list 
(list 1.123 -0.185) 
(list 0.5615 -0.185) 
(list 0.55946 -0.17472) 
(list 0.55339 -0.16444) 
(list 0.54348 -0.15417) 
(list 0.53003 -0.14389) 
(list 0.51345 -0.13361) 
(list 0.49425 -0.12333) 
(list 0.473 -0.11306) 
(list 0.45036 -0.10278) 
(list 0.427 -0.0925) 
(list 0.40364 -0.082222) 
(list 0.381 -0.071944) 
(list 0.35975 -0.061667) 
(list 0.34054 -0.051389) 
(list 0.32397 -0.041111) 
(list 0.31052 -0.030833) 
(list 0.30061 -0.020556) 
(list 0.29454 -0.010278) 
(list 0.2925 0) 
(list 0.29454 0.010278) 
(list 0.30061 0.020556) 
(list 0.31052 0.030833) 
(list 0.32397 0.041111) 
(list 0.34054 0.051389) 
(list 0.35975 0.061667) 
(list 0.381 0.071944) 
(list 0.40364 0.082222) 
(list 0.427 0.0925) 
(list 0.45036 0.10278) 
(list 0.473 0.11306) 
(list 0.49425 0.12333) 
(list 0.51345 0.13361) 
(list 0.53003 0.14389) 
(list 0.54348 0.15417) 
(list 0.55339 0.16444) 
(list 0.55946 0.17472) 
(list 0.5615 0.185) 
(list 1.123 0.185)))
(apply 'command (append '("pline") coords '("c")))
(setq uc2 (ssadd (entlast) uc2))
(command "_block" "blkuc2" "0,0.185" uc2 "")
(command "_insert" "blkuc2" "640,872.62" "1" "1" "0")
(command "_insert" "blkuc2" "640,872.25" "1" "1" "180")
(command "_insert" "blkuc2" "640,872.99" "1" "1" "0")
(command "_insert" "blkuc2" "640,872.62" "1" "1" "180")
(command "_insert" "blkuc2" "640,873.36" "1" "1" "0")
(command "_insert" "blkuc2" "640,872.99" "1" "1" "180")
(command "_insert" "blkuc2" "640,873.73" "1" "1" "0")
(command "_insert" "blkuc2" "640,873.36" "1" "1" "180")
(command "_insert" "blkuc2" "640,874.1" "1" "1" "0")
(command "_insert" "blkuc2" "640,873.73" "1" "1" "180")
(command "_insert" "blkuc2" "640,874.47" "1" "1" "0")
(command "_insert" "blkuc2" "640,874.1" "1" "1" "180")
(command "_insert" "blkuc2" "640,874.84" "1" "1" "0")
(command "_insert" "blkuc2" "640,874.47" "1" "1" "180")
(command "_insert" "blkuc2" "640,875.21" "1" "1" "0")
(command "_insert" "blkuc2" "640,874.84" "1" "1" "180")
(command "_insert" "blkuc2" "640,875.58" "1" "1" "0")
(command "_insert" "blkuc2" "640,875.21" "1" "1" "180")
(command "_insert" "blkuc2" "640,875.95" "1" "1" "0")
(command "_insert" "blkuc2" "640,875.58" "1" "1" "180")
(command "_insert" "blkuc2" "640,876.32" "1" "1" "0")
(command "_insert" "blkuc2" "640,875.95" "1" "1" "180")
(command "_insert" "blkuc2" "640,876.69" "1" "1" "0")
(command "_insert" "blkuc2" "640,876.32" "1" "1" "180")
(command "_insert" "blkuc2" "640,877.06" "1" "1" "0")
(command "_insert" "blkuc2" "640,876.69" "1" "1" "180")
(command "_insert" "blkuc2" "640,877.43" "1" "1" "0")
(command "_insert" "blkuc2" "640,877.06" "1" "1" "180")
(command "_insert" "blkuc2" "640,877.8" "1" "1" "0")
(command "_insert" "blkuc2" "640,877.43" "1" "1" "180")
(command "_insert" "blkuc2" "640,878.17" "1" "1" "0")
(command "_insert" "blkuc2" "640,877.8" "1" "1" "180")
(command "_insert" "blkuc2" "640,878.54" "1" "1" "0")
(command "_insert" "blkuc2" "640,878.17" "1" "1" "180")
(command "_insert" "blkuc2" "640,878.91" "1" "1" "0")
(command "_insert" "blkuc2" "640,878.54" "1" "1" "180")
(command "_insert" "blkuc2" "640,879.28" "1" "1" "0")
(command "_insert" "blkuc2" "640,878.91" "1" "1" "180")
(command "_insert" "blkuc2" "640,879.65" "1" "1" "0")
(command "_insert" "blkuc2" "640,879.28" "1" "1" "180")
(command "_insert" "blkuc2" "640,880.02" "1" "1" "0")
(command "_insert" "blkuc2" "640,879.65" "1" "1" "180")
(command "_insert" "blkuc2" "640,880.39" "1" "1" "0")
(command "_insert" "blkuc2" "640,880.02" "1" "1" "180")
(command "_insert" "blkuc2" "640,880.76" "1" "1" "0")
(command "_insert" "blkuc2" "640,880.39" "1" "1" "180")
(command "_insert" "blkuc2" "640,881.13" "1" "1" "0")
(command "_insert" "blkuc2" "640,880.76" "1" "1" "180")
(command "_insert" "blkuc2" "640,881.5" "1" "1" "0")
(command "_insert" "blkuc2" "640,881.13" "1" "1" "180")
(command "_insert" "blkuc2" "640,881.87" "1" "1" "0")
(command "_insert" "blkuc2" "640,881.5" "1" "1" "180")
(command "_insert" "blkuc2" "640,882.24" "1" "1" "0")
(command "_insert" "blkuc2" "640,881.87" "1" "1" "180")
(command "_insert" "blkuc2" "640,882.61" "1" "1" "0")
(command "_insert" "blkuc2" "640,882.24" "1" "1" "180")
(command "_insert" "blkuc2" "640,882.98" "1" "1" "0")
(command "_insert" "blkuc2" "640,882.61" "1" "1" "180")
(command "_insert" "blkuc2" "640,883.35" "1" "1" "0")
(command "_insert" "blkuc2" "640,882.98" "1" "1" "180")
(command "_insert" "blkuc2" "640,883.72" "1" "1" "0")
(command "_insert" "blkuc2" "640,883.35" "1" "1" "180")
(command "_insert" "blkuc2" "640,884.09" "1" "1" "0")
(command "_insert" "blkuc2" "640,883.72" "1" "1" "180")
(command "_insert" "blkuc2" "640,884.46" "1" "1" "0")
(command "_insert" "blkuc2" "640,884.09" "1" "1" "180")
(command "_insert" "blkuc2" "640,884.83" "1" "1" "0")
(command "_insert" "blkuc2" "640,884.46" "1" "1" "180")
(command "_insert" "blkuc2" "640,885.2" "1" "1" "0")
(command "_insert" "blkuc2" "640,884.83" "1" "1" "180")
(command "_insert" "blkuc2" "640,885.57" "1" "1" "0")
(command "_insert" "blkuc2" "640,885.2" "1" "1" "180")
(command "_insert" "blkuc2" "640,885.94" "1" "1" "0")
(command "_insert" "blkuc2" "640,885.57" "1" "1" "180")
(command "_insert" "blkuc2" "640,886.31" "1" "1" "0")
(command "_insert" "blkuc2" "640,885.94" "1" "1" "180")
(command "_insert" "blkuc2" "640,886.68" "1" "1" "0")
(command "_insert" "blkuc2" "640,886.31" "1" "1" "180")
(command "_insert" "blkuc2" "640,887.05" "1" "1" "0")
(command "_insert" "blkuc2" "640,886.68" "1" "1" "180")
(command "_insert" "blkuc2" "640,887.42" "1" "1" "0")
(command "_insert" "blkuc2" "640,887.05" "1" "1" "180")
(command "_insert" "blkuc2" "640,887.79" "1" "1" "0")
(command "_insert" "blkuc2" "640,887.42" "1" "1" "180")
(command "_insert" "blkuc2" "640,888.16" "1" "1" "0")
(command "_insert" "blkuc2" "640,887.79" "1" "1" "180")
(command "_insert" "blkuc2" "640,888.53" "1" "1" "0")
(command "_insert" "blkuc2" "640,888.16" "1" "1" "180")
(command "_insert" "blkuc2" "640,888.9" "1" "1" "0")
(command "_insert" "blkuc2" "640,888.53" "1" "1" "180")
(command "_insert" "blkuc2" "640,889.27" "1" "1" "0")
(command "_insert" "blkuc2" "640,888.9" "1" "1" "180")
(command "_insert" "blkuc2" "640,889.64" "1" "1" "0")
(command "_insert" "blkuc2" "640,889.27" "1" "1" "180")
(command "_insert" "blkuc2" "640,890.01" "1" "1" "0")
(command "_insert" "blkuc2" "640,889.64" "1" "1" "180")
(command "_insert" "blkuc2" "640,890.38" "1" "1" "0")
(command "_insert" "blkuc2" "640,890.01" "1" "1" "180")
(command "_insert" "blkuc2" "640,890.75" "1" "1" "0")
(command "_insert" "blkuc2" "640,890.38" "1" "1" "180")
(command "_insert" "blkuc2" "640,891.12" "1" "1" "0")
(command "_insert" "blkuc2" "640,890.75" "1" "1" "180")
(command "_insert" "blkuc2" "640,891.49" "1" "1" "0")
(command "_insert" "blkuc2" "640,891.12" "1" "1" "180")
(command "_insert" "blkuc2" "640,891.86" "1" "1" "0")
(command "_insert" "blkuc2" "640,891.49" "1" "1" "180")
(command "_insert" "blkuc2" "640,892.23" "1" "1" "0")
(command "_insert" "blkuc2" "640,891.86" "1" "1" "180")
(command "_insert" "blkuc2" "640,892.6" "1" "1" "0")
(command "_insert" "blkuc2" "640,892.23" "1" "1" "180")
(command "_insert" "blkuc2" "640,892.97" "1" "1" "0")
(command "_insert" "blkuc2" "640,892.6" "1" "1" "180")
(command "_insert" "blkuc2" "640,893.34" "1" "1" "0")
(command "_insert" "blkuc2" "640,892.97" "1" "1" "180")
(command "_insert" "blkuc2" "640,893.71" "1" "1" "0")
(command "_insert" "blkuc2" "640,893.34" "1" "1" "180")
(command "_insert" "blkuc2" "640,894.08" "1" "1" "0")
(command "_insert" "blkuc2" "640,893.71" "1" "1" "180")
(command "_insert" "blkuc2" "640,894.45" "1" "1" "0")
(command "_insert" "blkuc2" "640,894.08" "1" "1" "180")
(command "_insert" "blkuc2" "640,894.82" "1" "1" "0")
(command "_insert" "blkuc2" "640,894.45" "1" "1" "180")
(command "_insert" "blkuc2" "640,895.19" "1" "1" "0")
(command "_insert" "blkuc2" "640,894.82" "1" "1" "180")
(command "_insert" "blkuc2" "640,895.56" "1" "1" "0")
(command "_insert" "blkuc2" "640,895.19" "1" "1" "180")
(command "_insert" "blkuc2" "640,895.93" "1" "1" "0")
(command "_insert" "blkuc2" "640,895.56" "1" "1" "180")
(command "_insert" "blkuc2" "640,896.3" "1" "1" "0")
(command "_insert" "blkuc2" "640,895.93" "1" "1" "180")
(command "_insert" "blkuc2" "640,896.67" "1" "1" "0")
(command "_insert" "blkuc2" "640,896.3" "1" "1" "180")
(command "_insert" "blkuc2" "640,897.04" "1" "1" "0")
(command "_insert" "blkuc2" "640,896.67" "1" "1" "180")
(command "_insert" "blkuc2" "640,897.41" "1" "1" "0")
(command "_insert" "blkuc2" "640,897.04" "1" "1" "180")
(command "_insert" "blkuc2" "640,897.78" "1" "1" "0")
(command "_insert" "blkuc2" "640,897.41" "1" "1" "180")
(command "_insert" "blkuc2" "640,898.15" "1" "1" "0")
(command "_insert" "blkuc2" "640,897.78" "1" "1" "180")
(command "_insert" "blkuc2" "640,898.52" "1" "1" "0")
(command "_insert" "blkuc2" "640,898.15" "1" "1" "180")
(command "_insert" "blkuc2" "640,898.89" "1" "1" "0")
(command "_insert" "blkuc2" "640,898.52" "1" "1" "180")
(command "_insert" "blkuc2" "640,899.26" "1" "1" "0")
(command "_insert" "blkuc2" "640,898.89" "1" "1" "180")
(command "_insert" "blkuc2" "640,899.63" "1" "1" "0")
(command "_insert" "blkuc2" "640,899.26" "1" "1" "180")
(command "_insert" "blkuc2" "640,900" "1" "1" "0")
(command "_insert" "blkuc2" "640,899.63" "1" "1" "180")
(command "_insert" "blkuc2" "640,900.37" "1" "1" "0")
(command "_insert" "blkuc2" "640,900" "1" "1" "180")
(command "_insert" "blkuc2" "640,900.74" "1" "1" "0")
(command "_insert" "blkuc2" "640,900.37" "1" "1" "180")
(command "_insert" "blkuc2" "640,901.11" "1" "1" "0")
(command "_insert" "blkuc2" "640,900.74" "1" "1" "180")
(command "_insert" "blkuc2" "640,901.48" "1" "1" "0")
(command "_insert" "blkuc2" "640,901.11" "1" "1" "180")
(command "_insert" "blkuc2" "640,901.85" "1" "1" "0")
(command "_insert" "blkuc2" "640,901.48" "1" "1" "180")
(command "_insert" "blkuc2" "640,902.22" "1" "1" "0")
(command "_insert" "blkuc2" "640,901.85" "1" "1" "180")
(command "_insert" "blkuc2" "640,902.59" "1" "1" "0")
(command "_insert" "blkuc2" "640,902.22" "1" "1" "180")
(command "_insert" "blkuc2" "640,902.96" "1" "1" "0")
(command "_insert" "blkuc2" "640,902.59" "1" "1" "180")
(command "_insert" "blkuc2" "640,903.33" "1" "1" "0")
(command "_insert" "blkuc2" "640,902.96" "1" "1" "180")
(command "_insert" "blkuc2" "640,903.7" "1" "1" "0")
(command "_insert" "blkuc2" "640,903.33" "1" "1" "180")
(command "_insert" "blkuc2" "640,904.07" "1" "1" "0")
(command "_insert" "blkuc2" "640,903.7" "1" "1" "180")
(command "_insert" "blkuc2" "640,904.44" "1" "1" "0")
(command "_insert" "blkuc2" "640,904.07" "1" "1" "180")
(command "_insert" "blkuc2" "640,904.81" "1" "1" "0")
(command "_insert" "blkuc2" "640,904.44" "1" "1" "180")
(command "_insert" "blkuc2" "640,905.18" "1" "1" "0")
(command "_insert" "blkuc2" "640,904.81" "1" "1" "180")
(command "_insert" "blkuc2" "640,905.55" "1" "1" "0")
(command "_insert" "blkuc2" "640,905.18" "1" "1" "180")
(command "_insert" "blkuc2" "640,905.92" "1" "1" "0")
(command "_insert" "blkuc2" "640,905.55" "1" "1" "180")
(command "_insert" "blkuc2" "640,906.29" "1" "1" "0")
(command "_insert" "blkuc2" "640,905.92" "1" "1" "180")
(command "_insert" "blkuc2" "640,906.66" "1" "1" "0")
(command "_insert" "blkuc2" "640,906.29" "1" "1" "180")
(command "_insert" "blkuc2" "640,907.03" "1" "1" "0")
(command "_insert" "blkuc2" "640,906.66" "1" "1" "180")
(command "_insert" "blkuc2" "640,907.4" "1" "1" "0")
(command "_insert" "blkuc2" "640,907.03" "1" "1" "180")
(command "_insert" "blkuc2" "640,907.77" "1" "1" "0")
(command "_insert" "blkuc2" "640,907.4" "1" "1" "180")
(command "_insert" "blkuc2" "640,908.14" "1" "1" "0")
(command "_insert" "blkuc2" "640,907.77" "1" "1" "180")
(command "_insert" "blkuc2" "640,908.51" "1" "1" "0")
(command "_insert" "blkuc2" "640,908.14" "1" "1" "180")
(command "_insert" "blkuc2" "640,908.88" "1" "1" "0")
(command "_insert" "blkuc2" "640,908.51" "1" "1" "180")
(command "_insert" "blkuc2" "640,909.25" "1" "1" "0")
(command "_insert" "blkuc2" "640,908.88" "1" "1" "180")
(command "_insert" "blkuc2" "640,909.62" "1" "1" "0")
(command "_insert" "blkuc2" "640,909.25" "1" "1" "180")
(command "_insert" "blkuc2" "640,909.99" "1" "1" "0")
(command "_insert" "blkuc2" "640,909.62" "1" "1" "180")
(command "_insert" "blkuc2" "640,910.36" "1" "1" "0")
(command "_insert" "blkuc2" "640,909.99" "1" "1" "180")
(command "_insert" "blkuc2" "640,910.73" "1" "1" "0")
(command "_insert" "blkuc2" "640,910.36" "1" "1" "180")
(command "_insert" "blkuc2" "640,911.1" "1" "1" "0")
(command "_insert" "blkuc2" "640,910.73" "1" "1" "180")
(command "_insert" "blkuc2" "640,911.47" "1" "1" "0")
(command "_insert" "blkuc2" "640,911.1" "1" "1" "180")
(command "_insert" "blkuc2" "640,911.84" "1" "1" "0")
(command "_insert" "blkuc2" "640,911.47" "1" "1" "180")
(command "_insert" "blkuc2" "640,912.21" "1" "1" "0")
(command "_insert" "blkuc2" "640,911.84" "1" "1" "180")
(command "_insert" "blkuc2" "640,912.58" "1" "1" "0")
(command "_insert" "blkuc2" "640,912.21" "1" "1" "180")
(command "_insert" "blkuc2" "640,912.95" "1" "1" "0")
(command "_insert" "blkuc2" "640,912.58" "1" "1" "180")
(command "_insert" "blkuc2" "640,913.32" "1" "1" "0")
(command "_insert" "blkuc2" "640,912.95" "1" "1" "180")
(command "_insert" "blkuc2" "640,913.69" "1" "1" "0")
(command "_insert" "blkuc2" "640,913.32" "1" "1" "180")
(command "_insert" "blkuc2" "640,914.06" "1" "1" "0")
(command "_insert" "blkuc2" "640,913.69" "1" "1" "180")
(command "_insert" "blkuc2" "640,914.43" "1" "1" "0")
(command "_insert" "blkuc2" "640,914.06" "1" "1" "180")
(command "_insert" "blkuc2" "640,914.8" "1" "1" "0")
(command "_insert" "blkuc2" "640,914.43" "1" "1" "180")
(command "_insert" "blkuc2" "640,915.17" "1" "1" "0")
(command "_insert" "blkuc2" "640,914.8" "1" "1" "180")
(command "_insert" "blkuc2" "640,915.54" "1" "1" "0")
(command "_insert" "blkuc2" "640,915.17" "1" "1" "180")
(command "_insert" "blkuc2" "640,915.91" "1" "1" "0")
(command "_insert" "blkuc2" "640,915.54" "1" "1" "180")
(command "_insert" "blkuc2" "640,916.28" "1" "1" "0")
(command "_insert" "blkuc2" "640,915.91" "1" "1" "180")
(command "_insert" "blkuc2" "640,916.65" "1" "1" "0")
(command "_insert" "blkuc2" "640,916.28" "1" "1" "180")
(command "_insert" "blkuc2" "640,917.02" "1" "1" "0")
(command "_insert" "blkuc2" "640,916.65" "1" "1" "180")
(command "_insert" "blkuc2" "640,917.39" "1" "1" "0")
(command "_insert" "blkuc2" "640,917.02" "1" "1" "180")
(command "_insert" "blkuc2" "640,917.76" "1" "1" "0")
(command "_insert" "blkuc2" "640,917.39" "1" "1" "180")
(command "_insert" "blkuc2" "640,918.13" "1" "1" "0")
(command "_insert" "blkuc2" "640,917.76" "1" "1" "180")
(command "_insert" "blkuc2" "640,918.5" "1" "1" "0")
(command "_insert" "blkuc2" "640,918.13" "1" "1" "180")
(command "_insert" "blkuc2" "640,918.87" "1" "1" "0")
(command "_insert" "blkuc2" "640,918.5" "1" "1" "180")
(command "_insert" "blkuc2" "640,919.24" "1" "1" "0")
(command "_insert" "blkuc2" "640,918.87" "1" "1" "180")
(command "_insert" "blkuc2" "640,919.61" "1" "1" "0")
(command "_insert" "blkuc2" "640,919.24" "1" "1" "180")
(command "_insert" "blkuc2" "640,919.98" "1" "1" "0")
(command "_insert" "blkuc2" "640,919.61" "1" "1" "180")
(command "_insert" "blkuc2" "640,920.35" "1" "1" "0")
(command "_insert" "blkuc2" "640,919.98" "1" "1" "180")
(command "_insert" "blkuc2" "640,920.72" "1" "1" "0")
(command "_insert" "blkuc2" "640,920.35" "1" "1" "180")
(command "_insert" "blkuc2" "640,921.09" "1" "1" "0")
(command "_insert" "blkuc2" "640,920.72" "1" "1" "180")
(command "_insert" "blkuc2" "640,921.46" "1" "1" "0")
(command "_insert" "blkuc2" "640,921.09" "1" "1" "180")
(command "_insert" "blkuc2" "640,921.83" "1" "1" "0")
(command "_insert" "blkuc2" "640,921.46" "1" "1" "180")
(command "_insert" "blkuc2" "640,922.2" "1" "1" "0")
(command "_insert" "blkuc2" "640,921.83" "1" "1" "180")
(command "_insert" "blkuc2" "640,922.57" "1" "1" "0")
(command "_insert" "blkuc2" "640,922.2" "1" "1" "180")
(command "_insert" "blkuc2" "640,922.94" "1" "1" "0")
(command "_insert" "blkuc2" "640,922.57" "1" "1" "180")
(command "_insert" "blkuc2" "640,923.31" "1" "1" "0")
(command "_insert" "blkuc2" "640,922.94" "1" "1" "180")
(command "_insert" "blkuc2" "640,923.68" "1" "1" "0")
(command "_insert" "blkuc2" "640,923.31" "1" "1" "180")
(command "_insert" "blkuc2" "640,924.05" "1" "1" "0")
(command "_insert" "blkuc2" "640,923.68" "1" "1" "180")
(command "_insert" "blkuc2" "640,924.42" "1" "1" "0")
(command "_insert" "blkuc2" "640,924.05" "1" "1" "180")
(command "_insert" "blkuc2" "640,924.79" "1" "1" "0")
(command "_insert" "blkuc2" "640,924.42" "1" "1" "180")
(command "_insert" "blkuc2" "640,925.16" "1" "1" "0")
(command "_insert" "blkuc2" "640,924.79" "1" "1" "180")
(command "_insert" "blkuc2" "640,925.53" "1" "1" "0")
(command "_insert" "blkuc2" "640,925.16" "1" "1" "180")
(command "_insert" "blkuc2" "640,925.9" "1" "1" "0")
(command "_insert" "blkuc2" "640,925.53" "1" "1" "180")
(command "_insert" "blkuc2" "640,926.27" "1" "1" "0")
(command "_insert" "blkuc2" "640,925.9" "1" "1" "180")
(command "_insert" "blkuc2" "640,926.64" "1" "1" "0")
(command "_insert" "blkuc2" "640,926.27" "1" "1" "180")
(command "_insert" "blkuc2" "640,927.01" "1" "1" "0")
(command "_insert" "blkuc2" "640,926.64" "1" "1" "180")
(command "_insert" "blkuc2" "640,927.38" "1" "1" "0")
(command "_insert" "blkuc2" "640,927.01" "1" "1" "180")
(command "_insert" "blkuc2" "640,927.75" "1" "1" "0")
(command "_insert" "blkuc2" "640,927.38" "1" "1" "180")
(command "_layer" "set" "phccover" "")
(command "_rectangle" "638.877,933.3" "641.123,866.7")
(command "_layer" "set" "nitride" "")
(setq phc2 currobj)
(command "_layer" "set" "cover" "")
(command "_rectangle" "638.877,836.7" "641.123,963.3")
(command "_layer" "set" "nitride" "")
(command "_layer" "set" "text" "")
(command "_circle" "637.927,846.7" "0.075")
(command "_circle" "637.552,846.7" "0.15")
(command "_circle" "637.177,846.7" "0.075")
(command "_circle" "636.802,846.7" "0.15")
(command "_circle" "637.927,848.7" "0.075")
(command "_circle" "637.552,848.7" "0.075")
(command "_circle" "637.177,848.7" "0.15")
(command "_circle" "636.802,848.7" "0.15")
(command "_circle" "637.927,850.7" "0.075")
(command "_circle" "637.552,850.7" "0.15")
(command "_circle" "637.177,850.7" "0.15")
(command "_circle" "636.802,850.7" "0.15")
(command "_circle" "637.927,852.7" "0.075")
(command "_circle" "637.552,852.7" "0.075")
(command "_circle" "637.177,852.7" "0.075")
(command "_circle" "636.802,852.7" "0.075")
(command "_circle" "636.427,852.7" "0.15")
(command "_circle" "637.927,854.7" "0.075")
(command "_circle" "637.552,854.7" "0.15")
(command "_circle" "637.177,854.7" "0.075")
(command "_circle" "636.802,854.7" "0.075")
(command "_circle" "636.427,854.7" "0.15")
(command "_circle" "637.927,856.7" "0.075")
(command "_circle" "637.552,856.7" "0.075")
(command "_circle" "637.177,856.7" "0.15")
(command "_circle" "636.802,856.7" "0.075")
(command "_circle" "636.427,856.7" "0.15")
(command "_circle" "637.927,858.7" "0.075")
(command "_circle" "637.552,858.7" "0.15")
(command "_circle" "637.177,858.7" "0.15")
(command "_circle" "636.802,858.7" "0.075")
(command "_circle" "636.427,858.7" "0.15")
(command "_circle" "637.927,860.7" "0.075")
(command "_circle" "637.552,860.7" "0.075")
(command "_circle" "637.177,860.7" "0.075")
(command "_circle" "636.802,860.7" "0.15")
(command "_circle" "636.427,860.7" "0.15")
(command "_circle" "637.927,862.7" "0.075")
(command "_circle" "637.552,862.7" "0.15")
(command "_circle" "637.177,862.7" "0.075")
(command "_circle" "636.802,862.7" "0.15")
(command "_circle" "636.427,862.7" "0.15")
(command "_circle" "637.927,864.7" "0.075")
(command "_circle" "637.552,864.7" "0.075")
(command "_circle" "637.177,864.7" "0.15")
(command "_circle" "636.802,864.7" "0.15")
(command "_circle" "636.427,864.7" "0.15")
(command "_circle" "637.927,866.7" "0.075")
(command "_circle" "637.552,866.7" "0.15")
(command "_circle" "637.177,866.7" "0.15")
(command "_circle" "636.802,866.7" "0.15")
(command "_circle" "636.427,866.7" "0.15")
(command "_circle" "637.927,868.7" "0.075")
(command "_circle" "637.552,868.7" "0.075")
(command "_circle" "637.177,868.7" "0.075")
(command "_circle" "636.802,868.7" "0.075")
(command "_circle" "636.427,868.7" "0.075")
(command "_circle" "636.052,868.7" "0.15")
(command "_circle" "637.927,870.7" "0.075")
(command "_circle" "637.552,870.7" "0.15")
(command "_circle" "637.177,870.7" "0.075")
(command "_circle" "636.802,870.7" "0.075")
(command "_circle" "636.427,870.7" "0.075")
(command "_circle" "636.052,870.7" "0.15")
(command "_circle" "637.927,872.7" "0.075")
(command "_circle" "637.552,872.7" "0.075")
(command "_circle" "637.177,872.7" "0.15")
(command "_circle" "636.802,872.7" "0.075")
(command "_circle" "636.427,872.7" "0.075")
(command "_circle" "636.052,872.7" "0.15")
(command "_circle" "637.927,874.7" "0.075")
(command "_circle" "637.552,874.7" "0.15")
(command "_circle" "637.177,874.7" "0.15")
(command "_circle" "636.802,874.7" "0.075")
(command "_circle" "636.427,874.7" "0.075")
(command "_circle" "636.052,874.7" "0.15")
(command "_circle" "637.927,876.7" "0.075")
(command "_circle" "637.552,876.7" "0.075")
(command "_circle" "637.177,876.7" "0.075")
(command "_circle" "636.802,876.7" "0.15")
(command "_circle" "636.427,876.7" "0.075")
(command "_circle" "636.052,876.7" "0.15")
(command "_circle" "637.927,878.7" "0.075")
(command "_circle" "637.552,878.7" "0.15")
(command "_circle" "637.177,878.7" "0.075")
(command "_circle" "636.802,878.7" "0.15")
(command "_circle" "636.427,878.7" "0.075")
(command "_circle" "636.052,878.7" "0.15")
(command "_circle" "637.927,880.7" "0.075")
(command "_circle" "637.552,880.7" "0.075")
(command "_circle" "637.177,880.7" "0.15")
(command "_circle" "636.802,880.7" "0.15")
(command "_circle" "636.427,880.7" "0.075")
(command "_circle" "636.052,880.7" "0.15")
(command "_circle" "637.927,882.7" "0.075")
(command "_circle" "637.552,882.7" "0.15")
(command "_circle" "637.177,882.7" "0.15")
(command "_circle" "636.802,882.7" "0.15")
(command "_circle" "636.427,882.7" "0.075")
(command "_circle" "636.052,882.7" "0.15")
(command "_circle" "637.927,884.7" "0.075")
(command "_circle" "637.552,884.7" "0.075")
(command "_circle" "637.177,884.7" "0.075")
(command "_circle" "636.802,884.7" "0.075")
(command "_circle" "636.427,884.7" "0.15")
(command "_circle" "636.052,884.7" "0.15")
(command "_circle" "637.927,886.7" "0.075")
(command "_circle" "637.552,886.7" "0.15")
(command "_circle" "637.177,886.7" "0.075")
(command "_circle" "636.802,886.7" "0.075")
(command "_circle" "636.427,886.7" "0.15")
(command "_circle" "636.052,886.7" "0.15")
(command "_circle" "637.927,888.7" "0.075")
(command "_circle" "637.552,888.7" "0.075")
(command "_circle" "637.177,888.7" "0.15")
(command "_circle" "636.802,888.7" "0.075")
(command "_circle" "636.427,888.7" "0.15")
(command "_circle" "636.052,888.7" "0.15")
(command "_circle" "637.927,890.7" "0.075")
(command "_circle" "637.552,890.7" "0.15")
(command "_circle" "637.177,890.7" "0.15")
(command "_circle" "636.802,890.7" "0.075")
(command "_circle" "636.427,890.7" "0.15")
(command "_circle" "636.052,890.7" "0.15")
(command "_circle" "637.927,892.7" "0.075")
(command "_circle" "637.552,892.7" "0.075")
(command "_circle" "637.177,892.7" "0.075")
(command "_circle" "636.802,892.7" "0.15")
(command "_circle" "636.427,892.7" "0.15")
(command "_circle" "636.052,892.7" "0.15")
(command "_circle" "637.927,894.7" "0.075")
(command "_circle" "637.552,894.7" "0.15")
(command "_circle" "637.177,894.7" "0.075")
(command "_circle" "636.802,894.7" "0.15")
(command "_circle" "636.427,894.7" "0.15")
(command "_circle" "636.052,894.7" "0.15")
(command "_circle" "637.927,896.7" "0.075")
(command "_circle" "637.552,896.7" "0.075")
(command "_circle" "637.177,896.7" "0.15")
(command "_circle" "636.802,896.7" "0.15")
(command "_circle" "636.427,896.7" "0.15")
(command "_circle" "636.052,896.7" "0.15")
(command "_circle" "637.927,898.7" "0.075")
(command "_circle" "637.552,898.7" "0.15")
(command "_circle" "637.177,898.7" "0.15")
(command "_circle" "636.802,898.7" "0.15")
(command "_circle" "636.427,898.7" "0.15")
(command "_circle" "636.052,898.7" "0.15")
(command "_circle" "637.927,900.7" "0.075")
(command "_circle" "637.552,900.7" "0.075")
(command "_circle" "637.177,900.7" "0.075")
(command "_circle" "636.802,900.7" "0.075")
(command "_circle" "636.427,900.7" "0.075")
(command "_circle" "636.052,900.7" "0.075")
(command "_circle" "635.677,900.7" "0.15")
(command "_circle" "637.927,902.7" "0.075")
(command "_circle" "637.552,902.7" "0.15")
(command "_circle" "637.177,902.7" "0.075")
(command "_circle" "636.802,902.7" "0.075")
(command "_circle" "636.427,902.7" "0.075")
(command "_circle" "636.052,902.7" "0.075")
(command "_circle" "635.677,902.7" "0.15")
(command "_circle" "637.927,904.7" "0.075")
(command "_circle" "637.552,904.7" "0.075")
(command "_circle" "637.177,904.7" "0.15")
(command "_circle" "636.802,904.7" "0.075")
(command "_circle" "636.427,904.7" "0.075")
(command "_circle" "636.052,904.7" "0.075")
(command "_circle" "635.677,904.7" "0.15")
(command "_circle" "637.927,906.7" "0.075")
(command "_circle" "637.552,906.7" "0.15")
(command "_circle" "637.177,906.7" "0.15")
(command "_circle" "636.802,906.7" "0.075")
(command "_circle" "636.427,906.7" "0.075")
(command "_circle" "636.052,906.7" "0.075")
(command "_circle" "635.677,906.7" "0.15")
(command "_circle" "637.927,908.7" "0.075")
(command "_circle" "637.552,908.7" "0.075")
(command "_circle" "637.177,908.7" "0.075")
(command "_circle" "636.802,908.7" "0.15")
(command "_circle" "636.427,908.7" "0.075")
(command "_circle" "636.052,908.7" "0.075")
(command "_circle" "635.677,908.7" "0.15")
(command "_circle" "637.927,910.7" "0.075")
(command "_circle" "637.552,910.7" "0.15")
(command "_circle" "637.177,910.7" "0.075")
(command "_circle" "636.802,910.7" "0.15")
(command "_circle" "636.427,910.7" "0.075")
(command "_circle" "636.052,910.7" "0.075")
(command "_circle" "635.677,910.7" "0.15")
(command "_circle" "637.927,912.7" "0.075")
(command "_circle" "637.552,912.7" "0.075")
(command "_circle" "637.177,912.7" "0.15")
(command "_circle" "636.802,912.7" "0.15")
(command "_circle" "636.427,912.7" "0.075")
(command "_circle" "636.052,912.7" "0.075")
(command "_circle" "635.677,912.7" "0.15")
(command "_circle" "637.927,914.7" "0.075")
(command "_circle" "637.552,914.7" "0.15")
(command "_circle" "637.177,914.7" "0.15")
(command "_circle" "636.802,914.7" "0.15")
(command "_circle" "636.427,914.7" "0.075")
(command "_circle" "636.052,914.7" "0.075")
(command "_circle" "635.677,914.7" "0.15")
(command "_circle" "637.927,916.7" "0.075")
(command "_circle" "637.552,916.7" "0.075")
(command "_circle" "637.177,916.7" "0.075")
(command "_circle" "636.802,916.7" "0.075")
(command "_circle" "636.427,916.7" "0.15")
(command "_circle" "636.052,916.7" "0.075")
(command "_circle" "635.677,916.7" "0.15")
(command "_circle" "637.927,918.7" "0.075")
(command "_circle" "637.552,918.7" "0.15")
(command "_circle" "637.177,918.7" "0.075")
(command "_circle" "636.802,918.7" "0.075")
(command "_circle" "636.427,918.7" "0.15")
(command "_circle" "636.052,918.7" "0.075")
(command "_circle" "635.677,918.7" "0.15")
(command "_circle" "637.927,920.7" "0.075")
(command "_circle" "637.552,920.7" "0.075")
(command "_circle" "637.177,920.7" "0.15")
(command "_circle" "636.802,920.7" "0.075")
(command "_circle" "636.427,920.7" "0.15")
(command "_circle" "636.052,920.7" "0.075")
(command "_circle" "635.677,920.7" "0.15")
(command "_circle" "637.927,922.7" "0.075")
(command "_circle" "637.552,922.7" "0.15")
(command "_circle" "637.177,922.7" "0.15")
(command "_circle" "636.802,922.7" "0.075")
(command "_circle" "636.427,922.7" "0.15")
(command "_circle" "636.052,922.7" "0.075")
(command "_circle" "635.677,922.7" "0.15")
(command "_circle" "637.927,924.7" "0.075")
(command "_circle" "637.552,924.7" "0.075")
(command "_circle" "637.177,924.7" "0.075")
(command "_circle" "636.802,924.7" "0.15")
(command "_circle" "636.427,924.7" "0.15")
(command "_circle" "636.052,924.7" "0.075")
(command "_circle" "635.677,924.7" "0.15")
(command "_circle" "637.927,926.7" "0.075")
(command "_circle" "637.552,926.7" "0.15")
(command "_circle" "637.177,926.7" "0.075")
(command "_circle" "636.802,926.7" "0.15")
(command "_circle" "636.427,926.7" "0.15")
(command "_circle" "636.052,926.7" "0.075")
(command "_circle" "635.677,926.7" "0.15")
(command "_circle" "637.927,928.7" "0.075")
(command "_circle" "637.552,928.7" "0.075")
(command "_circle" "637.177,928.7" "0.15")
(command "_circle" "636.802,928.7" "0.15")
(command "_circle" "636.427,928.7" "0.15")
(command "_circle" "636.052,928.7" "0.075")
(command "_circle" "635.677,928.7" "0.15")
(command "_circle" "637.927,930.7" "0.075")
(command "_circle" "637.552,930.7" "0.15")
(command "_circle" "637.177,930.7" "0.15")
(command "_circle" "636.802,930.7" "0.15")
(command "_circle" "636.427,930.7" "0.15")
(command "_circle" "636.052,930.7" "0.075")
(command "_circle" "635.677,930.7" "0.15")
(command "_circle" "637.927,932.7" "0.075")
(command "_circle" "637.552,932.7" "0.075")
(command "_circle" "637.177,932.7" "0.075")
(command "_circle" "636.802,932.7" "0.075")
(command "_circle" "636.427,932.7" "0.075")
(command "_circle" "636.052,932.7" "0.15")
(command "_circle" "635.677,932.7" "0.15")
(command "_circle" "637.927,934.7" "0.075")
(command "_circle" "637.552,934.7" "0.15")
(command "_circle" "637.177,934.7" "0.075")
(command "_circle" "636.802,934.7" "0.075")
(command "_circle" "636.427,934.7" "0.075")
(command "_circle" "636.052,934.7" "0.15")
(command "_circle" "635.677,934.7" "0.15")
(command "_circle" "637.927,936.7" "0.075")
(command "_circle" "637.552,936.7" "0.075")
(command "_circle" "637.177,936.7" "0.15")
(command "_circle" "636.802,936.7" "0.075")
(command "_circle" "636.427,936.7" "0.075")
(command "_circle" "636.052,936.7" "0.15")
(command "_circle" "635.677,936.7" "0.15")
(command "_circle" "637.927,938.7" "0.075")
(command "_circle" "637.552,938.7" "0.15")
(command "_circle" "637.177,938.7" "0.15")
(command "_circle" "636.802,938.7" "0.075")
(command "_circle" "636.427,938.7" "0.075")
(command "_circle" "636.052,938.7" "0.15")
(command "_circle" "635.677,938.7" "0.15")
(command "_circle" "637.927,940.7" "0.075")
(command "_circle" "637.552,940.7" "0.075")
(command "_circle" "637.177,940.7" "0.075")
(command "_circle" "636.802,940.7" "0.15")
(command "_circle" "636.427,940.7" "0.075")
(command "_circle" "636.052,940.7" "0.15")
(command "_circle" "635.677,940.7" "0.15")
(command "_circle" "637.927,942.7" "0.075")
(command "_circle" "637.552,942.7" "0.15")
(command "_circle" "637.177,942.7" "0.075")
(command "_circle" "636.802,942.7" "0.15")
(command "_circle" "636.427,942.7" "0.075")
(command "_circle" "636.052,942.7" "0.15")
(command "_circle" "635.677,942.7" "0.15")
(command "_circle" "637.927,944.7" "0.075")
(command "_circle" "637.552,944.7" "0.075")
(command "_circle" "637.177,944.7" "0.15")
(command "_circle" "636.802,944.7" "0.15")
(command "_circle" "636.427,944.7" "0.075")
(command "_circle" "636.052,944.7" "0.15")
(command "_circle" "635.677,944.7" "0.15")
(command "_circle" "637.927,946.7" "0.075")
(command "_circle" "637.552,946.7" "0.15")
(command "_circle" "637.177,946.7" "0.15")
(command "_circle" "636.802,946.7" "0.15")
(command "_circle" "636.427,946.7" "0.075")
(command "_circle" "636.052,946.7" "0.15")
(command "_circle" "635.677,946.7" "0.15")
(command "_circle" "637.927,948.7" "0.075")
(command "_circle" "637.552,948.7" "0.075")
(command "_circle" "637.177,948.7" "0.075")
(command "_circle" "636.802,948.7" "0.075")
(command "_circle" "636.427,948.7" "0.15")
(command "_circle" "636.052,948.7" "0.15")
(command "_circle" "635.677,948.7" "0.15")
(command "_circle" "637.927,950.7" "0.075")
(command "_circle" "637.552,950.7" "0.15")
(command "_circle" "637.177,950.7" "0.075")
(command "_circle" "636.802,950.7" "0.075")
(command "_circle" "636.427,950.7" "0.15")
(command "_circle" "636.052,950.7" "0.15")
(command "_circle" "635.677,950.7" "0.15")
(command "_circle" "637.927,952.7" "0.075")
(command "_circle" "637.552,952.7" "0.075")
(command "_circle" "637.177,952.7" "0.15")
(command "_circle" "636.802,952.7" "0.075")
(command "_circle" "636.427,952.7" "0.15")
(command "_circle" "636.052,952.7" "0.15")
(command "_circle" "635.677,952.7" "0.15")
(command "_circle" "637.927,954.7" "0.075")
(command "_circle" "637.552,954.7" "0.15")
(command "_circle" "637.177,954.7" "0.15")
(command "_circle" "636.802,954.7" "0.075")
(command "_circle" "636.427,954.7" "0.15")
(command "_circle" "636.052,954.7" "0.15")
(command "_circle" "635.677,954.7" "0.15")
(command "_circle" "637.927,956.7" "0.075")
(command "_circle" "637.552,956.7" "0.075")
(command "_circle" "637.177,956.7" "0.075")
(command "_circle" "636.802,956.7" "0.15")
(command "_circle" "636.427,956.7" "0.15")
(command "_circle" "636.052,956.7" "0.15")
(command "_circle" "635.677,956.7" "0.15")
(command "_circle" "637.927,958.7" "0.075")
(command "_circle" "637.552,958.7" "0.15")
(command "_circle" "637.177,958.7" "0.075")
(command "_circle" "636.802,958.7" "0.15")
(command "_circle" "636.427,958.7" "0.15")
(command "_circle" "636.052,958.7" "0.15")
(command "_circle" "635.677,958.7" "0.15")
(command "_circle" "637.927,960.7" "0.075")
(command "_circle" "637.552,960.7" "0.075")
(command "_circle" "637.177,960.7" "0.15")
(command "_circle" "636.802,960.7" "0.15")
(command "_circle" "636.427,960.7" "0.15")
(command "_circle" "636.052,960.7" "0.15")
(command "_circle" "635.677,960.7" "0.15")
(command "_circle" "637.927,962.7" "0.075")
(command "_circle" "637.552,962.7" "0.15")
(command "_circle" "637.177,962.7" "0.15")
(command "_circle" "636.802,962.7" "0.15")
(command "_circle" "636.427,962.7" "0.15")
(command "_circle" "636.052,962.7" "0.15")
(command "_circle" "635.677,962.7" "0.15")
(command "_layer" "set" "nitride" "")
(command "_layer" "set" "text" "")
(command-s "_text" "626.877,963.3" "2" "-90" "a = 370 nm" )
(sssetfirst nil (ssget "_L"))
(if (not (numberp (vl-string-search "Mac" (getvar "platform")))) (c:txtexp))
(command "_layer" "set" "nitride" "")
(command "_layer" "set" "text" "")
(command-s "_text" "623.877,963.3" "2" "-90" "gap = 270 nm" )
(sssetfirst nil (ssget "_L"))
(if (not (numberp (vl-string-search "Mac" (getvar "platform")))) (c:txtexp))
(command "_layer" "set" "nitride" "")
(command "_layer" "set" "text" "")
(command-s "_text" "620.877,963.3" "2" "-90" "amplitude = 134.5 nm" )
(sssetfirst nil (ssget "_L"))
(if (not (numberp (vl-string-search "Mac" (getvar "platform")))) (c:txtexp))
(command "_layer" "set" "nitride" "")
(command "_layer" "set" "text" "")
(command-s "_text" "617.877,963.3" "2" "-90" "start width = 280 nm" )
(sssetfirst nil (ssget "_L"))
(if (not (numberp (vl-string-search "Mac" (getvar "platform")))) (c:txtexp))
(command "_layer" "set" "nitride" "")
(command "_layer" "set" "text" "")
(command-s "_text" "614.877,963.3" "2" "-90" "width = 292 nm" )
(sssetfirst nil (ssget "_L"))
(if (not (numberp (vl-string-search "Mac" (getvar "platform")))) (c:txtexp))
(command "_layer" "set" "nitride" "")
(command "_layer" "set" "text" "")
(command-s "_text" "611.877,963.3" "2" "-90" "taper: 15" )
(sssetfirst nil (ssget "_L"))
(if (not (numberp (vl-string-search "Mac" (getvar "platform")))) (c:txtexp))
(command "_layer" "set" "nitride" "")
(command "_layer" "set" "text" "")
(command-s "_text" "608.877,963.3" "2" "-90" "nominal: 150" )
(sssetfirst nil (ssget "_L"))
(if (not (numberp (vl-string-search "Mac" (getvar "platform")))) (c:txtexp))
(command "_layer" "set" "nitride" "")
(command "_layer" "set" "indicators" "")
(setq coords (list 
(list 560.415 940) 
(list 560.415 920) 
(list 540.415 900) 
(list 560.415 880) 
(list 560.415 860) 
(list 560.415 900) 
(list 560.415 887.0711) 
(list 547.4861 900) 
(list 560.415 912.9289) 
(list 560.415 900)))
(apply 'command (append '("pline") coords '("c")))
(command "._fillet" "radius" "1" "._fillet" "P" (entlast))
(setq coords (list 
(list 719.585 940) 
(list 719.585 920) 
(list 739.585 900) 
(list 719.585 880) 
(list 719.585 860) 
(list 719.585 900) 
(list 719.585 887.0711) 
(list 732.5139 900) 
(list 719.585 912.9289) 
(list 719.585 900)))
(apply 'command (append '("pline") coords '("c")))
(command "._fillet" "radius" "1" "._fillet" "P" (entlast))
(command "_layer" "set" "holes" "")
(command "_circle" "558.0629,914.1124" "0.5")
(command "_circle" "555.7109,911.7603" "0.5")
(command "_circle" "553.3588,909.4083" "0.5")
(command "_circle" "551.0067,907.0562" "0.5")
(command "_circle" "548.6547,904.7041" "0.5")
(command "_circle" "546.3026,902.3521" "0.5")
(command "_circle" "543.9505,900" "0.5")
(command "_circle" "546.3026,897.6479" "0.5")
(command "_circle" "548.6547,895.2959" "0.5")
(command "_circle" "551.0067,892.9438" "0.5")
(command "_circle" "553.3588,890.5917" "0.5")
(command "_circle" "555.7109,888.2397" "0.5")
(command "_circle" "558.0629,885.8876" "0.5")
(command "_circle" "721.9371,914.1124" "0.5")
(command "_circle" "724.2891,911.7603" "0.5")
(command "_circle" "726.6412,909.4083" "0.5")
(command "_circle" "728.9933,907.0562" "0.5")
(command "_circle" "731.3453,904.7041" "0.5")
(command "_circle" "733.6974,902.3521" "0.5")
(command "_circle" "736.0495,900" "0.5")
(command "_circle" "733.6974,897.6479" "0.5")
(command "_circle" "731.3453,895.2959" "0.5")
(command "_circle" "728.9933,892.9438" "0.5")
(command "_circle" "726.6412,890.5917" "0.5")
(command "_circle" "724.2891,888.2397" "0.5")
(command "_circle" "721.9371,885.8876" "0.5")
(command "_layer" "set" "nitride" "")
(command "_block" "blkcoupler2" "640,900" coupler2 "")
(command "_insert" "blkcoupler2" "640,900" "1" "1" "0")
(command "_insert" "blkcoupler2" "640,900" "1" "1" "180")
(command "_block" "blksinglenanobeam2" "640,900" singlenanobeam2 "")
(command "_insert" "blksinglenanobeam2" "640,900" "1" "1" "0")
(command "_insert" "blksinglenanobeam2" "640,900" "1" "1" "180")
(command "_block" "blkanglednodearray2" "640,900" anglednodearray2 "")
(command "_insert" "blkanglednodearray2" "640,900" "1" "1" "0")
(command "_insert" "blkanglednodearray2" "640,900" "1" "1" "180")
(command "_block" "blkcooledsinglenanobeam2" "640,900" cooledsinglenanobeam2 "")
(command "_insert" "blkcooledsinglenanobeam2" "640,900" "1" "1" "0")
(command "_insert" "blkcooledsinglenanobeam2" "640,900" "1" "1" "180")
(command "_block" "blkyjunction2" "640,900" yjunction2 "")
(command "_insert" "blkyjunction2" "640,900" "1" "1" "0")
(command "_insert" "blkyjunction2" "640,900" "1" "1" "180")
; DRAWING BULGING VEE GROOVE
(command "_layer" "set" "vgroove" "")
(setq coords (list 
(list 565.415 -605) 
(list 565.415 0) 
(list 565.415 0) 
(list 565.415 1800) 
(list 565.415 1800) 
(list 565.415 2405) 
(list 714.585 2405) 
(list 714.585 1800) 
(list 714.585 1800) 
(list 714.585 0) 
(list 714.585 0) 
(list 714.585 -605)))
(apply 'command (append '("pline") coords '("c")))
(command "._fillet" "radius" "0" "._fillet" "P" (entlast))
(command "_layer" "set" "window" "")
(command "_rectangle" "565.415,-1935" "714.585,-600")
(command "_rectangle" "565.415,2400" "714.585,5300")
(command "_layer" "set" "grid" "")
(command "_rectangle" "566.415,-1934" "589.9433,-1909.2133")
(command "_array" "last" "" "R" "75" "3" "25.7867" "24.5283")
(command "_rectangle" "641,-1934" "664.5283,-1909.2133")
(command "_array" "last" "" "R" "75" "3" "25.7867" "24.5283")
(command "_rectangle" "566.415,1" "589.9433,25.7")
(command "_array" "last" "" "R" "70" "3" "25.7" "24.5283")
(command "_rectangle" "641,1" "664.5283,25.7")
(command "_array" "last" "" "R" "70" "3" "25.7" "24.5283")
(command "_rectangle" "566.415,1801" "589.9433,1825.9185")
(command "_array" "last" "" "R" "135" "3" "25.9185" "24.5283")
(command "_rectangle" "641,1801" "664.5283,1825.9185")
(command "_array" "last" "" "R" "135" "3" "25.9185" "24.5283")
(command "_layer" "set" "vgrooveFDA" "")
(command "_rectangle" "714.585,-2233" "565.415,-1933")
(command "_layer" "set" "nitride" "")
(command "_layer" "set" "holes" "")
(command "_circle" "717.085,331.5" "0.5")
(command "_array" "last" "" "R" "379" "1" "3" "2.5")
(command "_circle" "562.915,331.5" "0.5")
(command "_array" "last" "" "R" "379" "1" "3" "-2.5")
(command "_layer" "set" "nitride" "")
(command "_layer" "set" "window" "")
(command "_layer" "set" "window" "")
(command "_rectangle" "719.585,0" "880.415,1800")
(command "._fillet" "radius" "20" "._fillet" "P" (entlast))
(command "_layer" "set" "grid" "")
(command "_rectangle" "720.585,1" "742.4179,25.7")
(command "_array" "last" "" "R" "70" "7" "25.7" "22.8329")
(command "_layer" "set" "nitride" "")
; DRAWING REGION LAYER
(command "_layer" "set" "regionLayer2" "")
(command "_rectangle" "560,-460" "720,2260")
(command "_layer" "set" "nitride" "")
(setq coupler2 nil)
(setq singlenanobeam2 nil)
(setq anglednodearray2 nil)
(setq cooledsinglenanobeam2 nil)
(setq yjunction2 nil)
; DEVICE #3
(command "_layer" "set" "window" "")
(command "_circle" "872.915,-415" "5")
(command "_circle" "872.915,-402.5" "5")
(command "_circle" "872.915,-390" "5")
(command "_layer" "set" "nitride" "")
(setq currobj nil)
(setq currobj (ssadd))
; DRAWING COUPLER
(setq coords (list 
(list 960.0645 -415) 
(list 960.0645 -413) 
(list 1033.585 -413) 
(list 1033.585 -413) 
(list 1033.9677 -413.0761) 
(list 1034.2921 -413.2929) 
(list 1034.5089 -413.6173) 
(list 1034.585 -414) 
(list 1034.585 -411.8) 
(list 1034.585 -411.8) 
(list 1034.5089 -412.1827) 
(list 1034.2921 -412.5071) 
(list 1033.9677 -412.7239) 
(list 1033.585 -412.8) 
(list 960.0645 -412.8) 
(list 960.0645 -410.8) 
(list 959.9355 -410.8) 
(list 959.9355 -412.8) 
(list 886.415 -412.8) 
(list 886.0323 -412.7239) 
(list 885.7079 -412.5071) 
(list 885.4911 -412.1827) 
(list 885.415 -411.8) 
(list 885.415 -411.8) 
(list 885.415 -414) 
(list 885.4911 -413.6173) 
(list 885.7079 -413.2929) 
(list 886.0323 -413.0761) 
(list 886.415 -413) 
(list 886.415 -413) 
(list 959.9355 -413) 
(list 959.9355 -415)))
(apply 'command (append '("pline") coords '("c")))
(setq currobj (ssadd (entlast) currobj))
(command "._fillet" "radius" "0.3" "._fillet" "P" (entlast))
(command "_layer" "set" "holes" "")
(command "_circle" "960,-412.9" "0.113")
(setq currobj (ssadd (entlast) currobj))
(command "_layer" "set" "nitride" "")
(command "_layer" "set" "text" "")
(command "_circle" "959.2,-415" "0.075")
(command "_circle" "959.2,-414.7" "0.075")
(command "_circle" "959.2,-414.4" "0.075")
(command "_circle" "958.9,-415" "0.075")
(command "_circle" "958.9,-414.7" "0.075")
(command "_circle" "958.9,-414.4" "0.075")
(command "_circle" "958.6,-415" "0.075")
(command "_circle" "958.6,-414.7" "0.075")
(command "_circle" "958.6,-414.4" "0.075")
(command "_layer" "set" "nitride" "")
(command "_layer" "set" "prebias" "")
(command "_rectangle" "885.415,-414" "1034.585,-411.8")
(setq currobj (ssadd (entlast) currobj))
(command "_rectangle" "959.9355,-415" "960.0645,-410.8")
(setq currobj (ssadd (entlast) currobj))
(command "_layer" "set" "nitride" "")
(setq coupler3 currobj)
(setq currobj nil)
(setq currobj (ssadd))
; DRAWING SINGLE NANOBEAM
(setq coords (list 
(list 960.0645 -410.8) 
(list 960.0645 -409.1417) 
(list 960.0645 -407.4833) 
(list 960.0645 -405.825) 
(list 960.0645 -404.1667) 
(list 960.0645 -402.5083) 
(list 960.0645 -400.85) 
(list 960.0645 -399.1917) 
(list 960.0645 -397.5333) 
(list 960.0646 -395.875) 
(list 960.0646 -394.2167) 
(list 960.0646 -392.5583) 
(list 960.0646 -390.9) 
(list 960.0647 -389.2417) 
(list 960.0647 -387.5833) 
(list 960.0647 -385.925) 
(list 960.0648 -384.2667) 
(list 960.0648 -382.6083) 
(list 960.0649 -380.95) 
(list 960.065 -379.2917) 
(list 960.0651 -377.6333) 
(list 960.0651 -375.975) 
(list 960.0652 -374.3167) 
(list 960.0653 -372.6583) 
(list 960.0655 -371) 
(list 960.0656 -369.3417) 
(list 960.0657 -367.6833) 
(list 960.0659 -366.025) 
(list 960.066 -364.3667) 
(list 960.0662 -362.7083) 
(list 960.0664 -361.05) 
(list 960.0666 -359.3917) 
(list 960.0668 -357.7333) 
(list 960.067 -356.075) 
(list 960.0672 -354.4167) 
(list 960.0675 -352.7583) 
(list 960.0678 -351.1) 
(list 960.068 -349.4417) 
(list 960.0683 -347.7833) 
(list 960.0686 -346.125) 
(list 960.069 -344.4667) 
(list 960.0693 -342.8083) 
(list 960.0697 -341.15) 
(list 960.07 -339.4917) 
(list 960.0704 -337.8333) 
(list 960.0709 -336.175) 
(list 960.0713 -334.5167) 
(list 960.0717 -332.8583) 
(list 960.0722 -331.2) 
(list 960.0727 -329.5417) 
(list 960.0732 -327.8833) 
(list 960.0738 -326.225) 
(list 960.0743 -324.5667) 
(list 960.0749 -322.9083) 
(list 960.0755 -321.25) 
(list 960.0761 -319.5917) 
(list 960.0767 -317.9333) 
(list 960.0774 -316.275) 
(list 960.0781 -314.6167) 
(list 960.0788 -312.9583) 
(list 960.0796 -311.3) 
(list 960.0803 -309.6417) 
(list 960.0811 -307.9833) 
(list 960.0819 -306.325) 
(list 960.0828 -304.6667) 
(list 960.0837 -303.0083) 
(list 960.0845 -301.35) 
(list 960.0855 -299.6917) 
(list 960.0864 -298.0333) 
(list 960.0874 -296.375) 
(list 960.0884 -294.7167) 
(list 960.0895 -293.0583) 
(list 960.0905 -291.4) 
(list 960.0916 -289.7417) 
(list 960.0928 -288.0833) 
(list 960.0939 -286.425) 
(list 960.0951 -284.7667) 
(list 960.0963 -283.1083) 
(list 960.0976 -281.45) 
(list 960.0989 -279.7917) 
(list 960.1002 -278.1333) 
(list 960.1016 -276.475) 
(list 960.1029 -274.8167) 
(list 960.1044 -273.1583) 
(list 960.1058 -271.5) 
(list 960.1073 -269.8417) 
(list 960.1089 -268.1833) 
(list 960.1104 -266.525) 
(list 960.112 -264.8667) 
(list 960.1137 -263.2083) 
(list 960.1153 -261.55) 
(list 960.117 -259.8917) 
(list 960.1188 -258.2333) 
(list 960.1206 -256.575) 
(list 960.1224 -254.9167) 
(list 960.1243 -253.2583) 
(list 960.1262 -251.6) 
(list 960.1281 -249.9417) 
(list 960.1301 -248.2833) 
(list 960.1322 -246.625) 
(list 960.1342 -244.9667) 
(list 960.1363 -243.3083) 
(list 960.1385 -241.65) 
(list 960.1407 -239.9917) 
(list 960.1429 -238.3333) 
(list 960.1452 -236.675) 
(list 960.1476 -235.0167) 
(list 960.1499 -233.3583) 
(list 960.1523 -231.7) 
(list 960.1548 -230.0417) 
(list 960.1573 -228.3833) 
(list 960.1599 -226.725) 
(list 960.1625 -225.0667) 
(list 960.1651 -223.4083) 
(list 960.1678 -221.75) 
(list 960.1706 -220.0917) 
(list 960.1733 -218.4333) 
(list 960.1762 -216.775) 
(list 960.1791 -215.1167) 
(list 960.182 -213.4583) 
(list 960.185 -211.8) 
(list 959.815 -211.8) 
(list 959.818 -213.4583) 
(list 959.8209 -215.1167) 
(list 959.8238 -216.775) 
(list 959.8267 -218.4333) 
(list 959.8294 -220.0917) 
(list 959.8322 -221.75) 
(list 959.8349 -223.4083) 
(list 959.8375 -225.0667) 
(list 959.8401 -226.725) 
(list 959.8427 -228.3833) 
(list 959.8452 -230.0417) 
(list 959.8477 -231.7) 
(list 959.8501 -233.3583) 
(list 959.8524 -235.0167) 
(list 959.8548 -236.675) 
(list 959.8571 -238.3333) 
(list 959.8593 -239.9917) 
(list 959.8615 -241.65) 
(list 959.8637 -243.3083) 
(list 959.8658 -244.9667) 
(list 959.8678 -246.625) 
(list 959.8699 -248.2833) 
(list 959.8719 -249.9417) 
(list 959.8738 -251.6) 
(list 959.8757 -253.2583) 
(list 959.8776 -254.9167) 
(list 959.8794 -256.575) 
(list 959.8812 -258.2333) 
(list 959.883 -259.8917) 
(list 959.8847 -261.55) 
(list 959.8863 -263.2083) 
(list 959.888 -264.8667) 
(list 959.8896 -266.525) 
(list 959.8911 -268.1833) 
(list 959.8927 -269.8417) 
(list 959.8942 -271.5) 
(list 959.8956 -273.1583) 
(list 959.8971 -274.8167) 
(list 959.8984 -276.475) 
(list 959.8998 -278.1333) 
(list 959.9011 -279.7917) 
(list 959.9024 -281.45) 
(list 959.9037 -283.1083) 
(list 959.9049 -284.7667) 
(list 959.9061 -286.425) 
(list 959.9072 -288.0833) 
(list 959.9084 -289.7417) 
(list 959.9095 -291.4) 
(list 959.9105 -293.0583) 
(list 959.9116 -294.7167) 
(list 959.9126 -296.375) 
(list 959.9136 -298.0333) 
(list 959.9145 -299.6917) 
(list 959.9155 -301.35) 
(list 959.9163 -303.0083) 
(list 959.9172 -304.6667) 
(list 959.9181 -306.325) 
(list 959.9189 -307.9833) 
(list 959.9197 -309.6417) 
(list 959.9204 -311.3) 
(list 959.9212 -312.9583) 
(list 959.9219 -314.6167) 
(list 959.9226 -316.275) 
(list 959.9233 -317.9333) 
(list 959.9239 -319.5917) 
(list 959.9245 -321.25) 
(list 959.9251 -322.9083) 
(list 959.9257 -324.5667) 
(list 959.9262 -326.225) 
(list 959.9268 -327.8833) 
(list 959.9273 -329.5417) 
(list 959.9278 -331.2) 
(list 959.9283 -332.8583) 
(list 959.9287 -334.5167) 
(list 959.9291 -336.175) 
(list 959.9296 -337.8333) 
(list 959.93 -339.4917) 
(list 959.9303 -341.15) 
(list 959.9307 -342.8083) 
(list 959.931 -344.4667) 
(list 959.9314 -346.125) 
(list 959.9317 -347.7833) 
(list 959.932 -349.4417) 
(list 959.9322 -351.1) 
(list 959.9325 -352.7583) 
(list 959.9328 -354.4167) 
(list 959.933 -356.075) 
(list 959.9332 -357.7333) 
(list 959.9334 -359.3917) 
(list 959.9336 -361.05) 
(list 959.9338 -362.7083) 
(list 959.934 -364.3667) 
(list 959.9341 -366.025) 
(list 959.9343 -367.6833) 
(list 959.9344 -369.3417) 
(list 959.9345 -371) 
(list 959.9347 -372.6583) 
(list 959.9348 -374.3167) 
(list 959.9349 -375.975) 
(list 959.9349 -377.6333) 
(list 959.935 -379.2917) 
(list 959.9351 -380.95) 
(list 959.9352 -382.6083) 
(list 959.9352 -384.2667) 
(list 959.9353 -385.925) 
(list 959.9353 -387.5833) 
(list 959.9353 -389.2417) 
(list 959.9354 -390.9) 
(list 959.9354 -392.5583) 
(list 959.9354 -394.2167) 
(list 959.9354 -395.875) 
(list 959.9355 -397.5333) 
(list 959.9355 -399.1917) 
(list 959.9355 -400.85) 
(list 959.9355 -402.5083) 
(list 959.9355 -404.1667) 
(list 959.9355 -405.825) 
(list 959.9355 -407.4833) 
(list 959.9355 -409.1417) 
(list 959.9355 -410.8)))
(apply 'command (append '("pline") coords '("c")))
(setq currobj (ssadd (entlast) currobj))
(command "_layer" "set" "prebias" "")
(command "_rectangle" "959.815,-410.8" "960.185,-211.8")
(setq currobj (ssadd (entlast) currobj))
(command "_layer" "set" "nitride" "")
(setq singlenanobeam3 currobj)
(setq currobj nil)
(setq currobj (ssadd))
; DRAWING NODE ARRAY
(setq coords (list 
(list 960.185 -211.8) 
(list 960.5625 -201.8) 
(list 960.5625 -201.8) 
(list 960.5625 -200.8) 
(list 1034.585 -212.6864) 
(list 1034.585 -207.7434) 
(list 960.5625 -197.357) 
(list 960.5625 -196.357) 
(list 960.5625 -196.357) 
(list 960.2625 -186.357) 
(list 959.7375 -186.357) 
(list 959.4375 -196.357) 
(list 959.4375 -196.357) 
(list 959.4375 -197.357) 
(list 885.415 -207.7434) 
(list 885.415 -212.6864) 
(list 959.4375 -200.8) 
(list 959.4375 -201.8) 
(list 959.4375 -201.8) 
(list 959.815 -211.8)))
(apply 'command (append '("pline") coords '("c")))
(setq currobj (ssadd (entlast) currobj))
(command "_layer" "set" "prebias" "")
(setq coords (list 
(list 959.4375 -212.6864) 
(list 959.4375 -200.8) 
(list 885.415 -212.6864) 
(list 885.415 -207.7434) 
(list 959.4375 -197.357) 
(list 959.4375 -186.357) 
(list 960.5625 -186.357) 
(list 960.5625 -197.357) 
(list 1034.585 -207.7434) 
(list 1034.585 -212.6864) 
(list 960.5625 -200.8) 
(list 960.5625 -212.6864)))
(apply 'command (append '("pline") coords '("c")))
(setq currobj (ssadd (entlast) currobj))
(command "_layer" "set" "nitride" "")
(command "_layer" "set" "fda1" "")
(setq coords (list 
(list 960.5625 -200.657) 
(list 1034.585 -212.5434) 
(list 1034.585 -212.3664) 
(list 960.5625 -200.58)))
(apply 'command (append '("pline") coords '("c")))
(setq currobj (ssadd (entlast) currobj))
(setq coords (list 
(list 960.5625 -200.437) 
(list 1034.585 -212.2234) 
(list 1034.585 -212.0464) 
(list 960.5625 -200.36)))
(apply 'command (append '("pline") coords '("c")))
(setq currobj (ssadd (entlast) currobj))
(setq coords (list 
(list 960.5625 -200.217) 
(list 1034.585 -211.9034) 
(list 1034.585 -211.7264) 
(list 960.5625 -200.14)))
(apply 'command (append '("pline") coords '("c")))
(setq currobj (ssadd (entlast) currobj))
(setq coords (list 
(list 960.5625 -199.997) 
(list 1034.585 -211.5834) 
(list 1034.585 -211.4064) 
(list 960.5625 -199.92)))
(apply 'command (append '("pline") coords '("c")))
(setq currobj (ssadd (entlast) currobj))
(setq coords (list 
(list 960.5625 -199.777) 
(list 1034.585 -211.2634) 
(list 1034.585 -211.0864) 
(list 960.5625 -199.7)))
(apply 'command (append '("pline") coords '("c")))
(setq currobj (ssadd (entlast) currobj))
(setq coords (list 
(list 960.5625 -199.557) 
(list 1034.585 -210.9434) 
(list 1034.585 -210.7664) 
(list 960.5625 -199.48)))
(apply 'command (append '("pline") coords '("c")))
(setq currobj (ssadd (entlast) currobj))
(setq coords (list 
(list 960.5625 -199.337) 
(list 1034.585 -210.6234) 
(list 1034.585 -210.4464) 
(list 960.5625 -199.26)))
(apply 'command (append '("pline") coords '("c")))
(setq currobj (ssadd (entlast) currobj))
(setq coords (list 
(list 960.5625 -199.117) 
(list 1034.585 -210.3034) 
(list 1034.585 -210.1264) 
(list 960.5625 -199.04)))
(apply 'command (append '("pline") coords '("c")))
(setq currobj (ssadd (entlast) currobj))
(setq coords (list 
(list 960.5625 -198.897) 
(list 1034.585 -209.9834) 
(list 1034.585 -209.8064) 
(list 960.5625 -198.82)))
(apply 'command (append '("pline") coords '("c")))
(setq currobj (ssadd (entlast) currobj))
(setq coords (list 
(list 960.5625 -198.677) 
(list 1034.585 -209.6634) 
(list 1034.585 -209.4864) 
(list 960.5625 -198.6)))
(apply 'command (append '("pline") coords '("c")))
(setq currobj (ssadd (entlast) currobj))
(setq coords (list 
(list 960.5625 -198.457) 
(list 1034.585 -209.3434) 
(list 1034.585 -209.1664) 
(list 960.5625 -198.38)))
(apply 'command (append '("pline") coords '("c")))
(setq currobj (ssadd (entlast) currobj))
(setq coords (list 
(list 960.5625 -198.237) 
(list 1034.585 -209.0234) 
(list 1034.585 -208.8464) 
(list 960.5625 -198.16)))
(apply 'command (append '("pline") coords '("c")))
(setq currobj (ssadd (entlast) currobj))
(setq coords (list 
(list 960.5625 -198.017) 
(list 1034.585 -208.7034) 
(list 1034.585 -208.5264) 
(list 960.5625 -197.94)))
(apply 'command (append '("pline") coords '("c")))
(setq currobj (ssadd (entlast) currobj))
(setq coords (list 
(list 960.5625 -197.797) 
(list 1034.585 -208.3834) 
(list 1034.585 -208.2064) 
(list 960.5625 -197.72)))
(apply 'command (append '("pline") coords '("c")))
(setq currobj (ssadd (entlast) currobj))
(setq coords (list 
(list 960.5625 -197.577) 
(list 1034.585 -208.0634) 
(list 1034.585 -207.8864) 
(list 960.5625 -197.5)))
(apply 'command (append '("pline") coords '("c")))
(setq currobj (ssadd (entlast) currobj))
(setq coords (list 
(list 959.4375 -197.5) 
(list 885.415 -207.8864) 
(list 885.415 -208.0634) 
(list 959.4375 -197.577)))
(apply 'command (append '("pline") coords '("c")))
(setq currobj (ssadd (entlast) currobj))
(setq coords (list 
(list 959.4375 -197.72) 
(list 885.415 -208.2064) 
(list 885.415 -208.3834) 
(list 959.4375 -197.797)))
(apply 'command (append '("pline") coords '("c")))
(setq currobj (ssadd (entlast) currobj))
(setq coords (list 
(list 959.4375 -197.94) 
(list 885.415 -208.5264) 
(list 885.415 -208.7034) 
(list 959.4375 -198.017)))
(apply 'command (append '("pline") coords '("c")))
(setq currobj (ssadd (entlast) currobj))
(setq coords (list 
(list 959.4375 -198.16) 
(list 885.415 -208.8464) 
(list 885.415 -209.0234) 
(list 959.4375 -198.237)))
(apply 'command (append '("pline") coords '("c")))
(setq currobj (ssadd (entlast) currobj))
(setq coords (list 
(list 959.4375 -198.38) 
(list 885.415 -209.1664) 
(list 885.415 -209.3434) 
(list 959.4375 -198.457)))
(apply 'command (append '("pline") coords '("c")))
(setq currobj (ssadd (entlast) currobj))
(setq coords (list 
(list 959.4375 -198.6) 
(list 885.415 -209.4864) 
(list 885.415 -209.6634) 
(list 959.4375 -198.677)))
(apply 'command (append '("pline") coords '("c")))
(setq currobj (ssadd (entlast) currobj))
(setq coords (list 
(list 959.4375 -198.82) 
(list 885.415 -209.8064) 
(list 885.415 -209.9834) 
(list 959.4375 -198.897)))
(apply 'command (append '("pline") coords '("c")))
(setq currobj (ssadd (entlast) currobj))
(setq coords (list 
(list 959.4375 -199.04) 
(list 885.415 -210.1264) 
(list 885.415 -210.3034) 
(list 959.4375 -199.117)))
(apply 'command (append '("pline") coords '("c")))
(setq currobj (ssadd (entlast) currobj))
(setq coords (list 
(list 959.4375 -199.26) 
(list 885.415 -210.4464) 
(list 885.415 -210.6234) 
(list 959.4375 -199.337)))
(apply 'command (append '("pline") coords '("c")))
(setq currobj (ssadd (entlast) currobj))
(setq coords (list 
(list 959.4375 -199.48) 
(list 885.415 -210.7664) 
(list 885.415 -210.9434) 
(list 959.4375 -199.557)))
(apply 'command (append '("pline") coords '("c")))
(setq currobj (ssadd (entlast) currobj))
(setq coords (list 
(list 959.4375 -199.7) 
(list 885.415 -211.0864) 
(list 885.415 -211.2634) 
(list 959.4375 -199.777)))
(apply 'command (append '("pline") coords '("c")))
(setq currobj (ssadd (entlast) currobj))
(setq coords (list 
(list 959.4375 -199.92) 
(list 885.415 -211.4064) 
(list 885.415 -211.5834) 
(list 959.4375 -199.997)))
(apply 'command (append '("pline") coords '("c")))
(setq currobj (ssadd (entlast) currobj))
(setq coords (list 
(list 959.4375 -200.14) 
(list 885.415 -211.7264) 
(list 885.415 -211.9034) 
(list 959.4375 -200.217)))
(apply 'command (append '("pline") coords '("c")))
(setq currobj (ssadd (entlast) currobj))
(setq coords (list 
(list 959.4375 -200.36) 
(list 885.415 -212.0464) 
(list 885.415 -212.2234) 
(list 959.4375 -200.437)))
(apply 'command (append '("pline") coords '("c")))
(setq currobj (ssadd (entlast) currobj))
(setq coords (list 
(list 959.4375 -200.58) 
(list 885.415 -212.3664) 
(list 885.415 -212.5434) 
(list 959.4375 -200.657)))
(apply 'command (append '("pline") coords '("c")))
(setq currobj (ssadd (entlast) currobj))
(command "_layer" "set" "nitride" "")
(command "_layer" "set" "text" "")
(command "_circle" "958.985,-211.8" "0.075")
(command "_circle" "958.985,-211.5" "0.075")
(command "_circle" "958.985,-211.2" "0.075")
(command "_circle" "958.985,-210.9" "0.075")
(command "_circle" "958.985,-210.6" "0.075")
(command "_circle" "958.685,-211.8" "0.075")
(command "_circle" "958.685,-211.5" "0.075")
(command "_circle" "958.685,-211.2" "0.075")
(command "_circle" "958.685,-210.9" "0.075")
(command "_circle" "958.685,-210.6" "0.075")
(command "_circle" "958.385,-211.8" "0.075")
(command "_circle" "958.385,-211.5" "0.075")
(command "_circle" "958.385,-211.2" "0.075")
(command "_circle" "958.385,-210.9" "0.075")
(command "_circle" "958.385,-210.6" "0.075")
(command "_circle" "958.085,-211.8" "0.075")
(command "_circle" "958.085,-211.5" "0.075")
(command "_circle" "958.085,-211.2" "0.075")
(command "_circle" "958.085,-210.9" "0.075")
(command "_circle" "958.085,-210.6" "0.075")
(command "_circle" "957.785,-211.8" "0.075")
(command "_circle" "957.785,-211.5" "0.075")
(command "_circle" "957.785,-211.2" "0.075")
(command "_circle" "957.785,-210.9" "0.075")
(command "_circle" "957.785,-210.6" "0.075")
(command "_layer" "set" "nitride" "")
(setq anglednodearray3 currobj)
(setq currobj nil)
(setq currobj (ssadd))
; DRAWING COOLED SINGLE NANOBEAM
(setq coords (list 
(list 960.2625 -186.357) 
(list 960.2625 -181.357) 
(list 959.7375 -181.357) 
(list 959.7375 -186.357)))
(apply 'command (append '("pline") coords '("c")))
(setq currobj (ssadd (entlast) currobj))
(command "_layer" "set" "prebias" "")
(command "_rectangle" "959.7375,-186.357" "960.2625,-181.357")
(setq currobj (ssadd (entlast) currobj))
(command "_layer" "set" "nitride" "")
(setq coords (list 
(list 960.2625 -181.357) 
(list 960.5625 -171.357) 
(list 960.5625 -171.357) 
(list 960.5625 -170.357) 
(list 1034.585 -171.107) 
(list 1034.585 -166.164) 
(list 960.5625 -166.914) 
(list 960.5625 -165.914) 
(list 960.5625 -165.914) 
(list 960.2625 -155.914) 
(list 959.7375 -155.914) 
(list 959.4375 -165.914) 
(list 959.4375 -165.914) 
(list 959.4375 -166.914) 
(list 885.415 -166.164) 
(list 885.415 -171.107) 
(list 959.4375 -170.357) 
(list 959.4375 -171.357) 
(list 959.4375 -171.357) 
(list 959.7375 -181.357)))
(apply 'command (append '("pline") coords '("c")))
(setq currobj (ssadd (entlast) currobj))
(command "_layer" "set" "prebias" "")
(setq coords (list 
(list 959.4375 -181.357) 
(list 959.4375 -170.357) 
(list 885.415 -171.107) 
(list 885.415 -166.164) 
(list 959.4375 -166.914) 
(list 959.4375 -155.914) 
(list 960.5625 -155.914) 
(list 960.5625 -166.914) 
(list 1034.585 -166.164) 
(list 1034.585 -171.107) 
(list 960.5625 -170.357) 
(list 960.5625 -181.357)))
(apply 'command (append '("pline") coords '("c")))
(setq currobj (ssadd (entlast) currobj))
(command "_layer" "set" "nitride" "")
(command "_layer" "set" "fda1" "")
(setq coords (list 
(list 960.5625 -170.214) 
(list 1034.585 -170.964) 
(list 1034.585 -170.787) 
(list 960.5625 -170.137)))
(apply 'command (append '("pline") coords '("c")))
(setq currobj (ssadd (entlast) currobj))
(setq coords (list 
(list 960.5625 -169.994) 
(list 1034.585 -170.644) 
(list 1034.585 -170.467) 
(list 960.5625 -169.917)))
(apply 'command (append '("pline") coords '("c")))
(setq currobj (ssadd (entlast) currobj))
(setq coords (list 
(list 960.5625 -169.774) 
(list 1034.585 -170.324) 
(list 1034.585 -170.147) 
(list 960.5625 -169.697)))
(apply 'command (append '("pline") coords '("c")))
(setq currobj (ssadd (entlast) currobj))
(setq coords (list 
(list 960.5625 -169.554) 
(list 1034.585 -170.004) 
(list 1034.585 -169.827) 
(list 960.5625 -169.477)))
(apply 'command (append '("pline") coords '("c")))
(setq currobj (ssadd (entlast) currobj))
(setq coords (list 
(list 960.5625 -169.334) 
(list 1034.585 -169.684) 
(list 1034.585 -169.507) 
(list 960.5625 -169.257)))
(apply 'command (append '("pline") coords '("c")))
(setq currobj (ssadd (entlast) currobj))
(setq coords (list 
(list 960.5625 -169.114) 
(list 1034.585 -169.364) 
(list 1034.585 -169.187) 
(list 960.5625 -169.037)))
(apply 'command (append '("pline") coords '("c")))
(setq currobj (ssadd (entlast) currobj))
(setq coords (list 
(list 960.5625 -168.894) 
(list 1034.585 -169.044) 
(list 1034.585 -168.867) 
(list 960.5625 -168.817)))
(apply 'command (append '("pline") coords '("c")))
(setq currobj (ssadd (entlast) currobj))
(setq coords (list 
(list 960.5625 -168.674) 
(list 1034.585 -168.724) 
(list 1034.585 -168.547) 
(list 960.5625 -168.597)))
(apply 'command (append '("pline") coords '("c")))
(setq currobj (ssadd (entlast) currobj))
(setq coords (list 
(list 960.5625 -168.454) 
(list 1034.585 -168.404) 
(list 1034.585 -168.227) 
(list 960.5625 -168.377)))
(apply 'command (append '("pline") coords '("c")))
(setq currobj (ssadd (entlast) currobj))
(setq coords (list 
(list 960.5625 -168.234) 
(list 1034.585 -168.084) 
(list 1034.585 -167.907) 
(list 960.5625 -168.157)))
(apply 'command (append '("pline") coords '("c")))
(setq currobj (ssadd (entlast) currobj))
(setq coords (list 
(list 960.5625 -168.014) 
(list 1034.585 -167.764) 
(list 1034.585 -167.587) 
(list 960.5625 -167.937)))
(apply 'command (append '("pline") coords '("c")))
(setq currobj (ssadd (entlast) currobj))
(setq coords (list 
(list 960.5625 -167.794) 
(list 1034.585 -167.444) 
(list 1034.585 -167.267) 
(list 960.5625 -167.717)))
(apply 'command (append '("pline") coords '("c")))
(setq currobj (ssadd (entlast) currobj))
(setq coords (list 
(list 960.5625 -167.574) 
(list 1034.585 -167.124) 
(list 1034.585 -166.947) 
(list 960.5625 -167.497)))
(apply 'command (append '("pline") coords '("c")))
(setq currobj (ssadd (entlast) currobj))
(setq coords (list 
(list 960.5625 -167.354) 
(list 1034.585 -166.804) 
(list 1034.585 -166.627) 
(list 960.5625 -167.277)))
(apply 'command (append '("pline") coords '("c")))
(setq currobj (ssadd (entlast) currobj))
(setq coords (list 
(list 960.5625 -167.134) 
(list 1034.585 -166.484) 
(list 1034.585 -166.307) 
(list 960.5625 -167.057)))
(apply 'command (append '("pline") coords '("c")))
(setq currobj (ssadd (entlast) currobj))
(setq coords (list 
(list 959.4375 -167.057) 
(list 885.415 -166.307) 
(list 885.415 -166.484) 
(list 959.4375 -167.134)))
(apply 'command (append '("pline") coords '("c")))
(setq currobj (ssadd (entlast) currobj))
(setq coords (list 
(list 959.4375 -167.277) 
(list 885.415 -166.627) 
(list 885.415 -166.804) 
(list 959.4375 -167.354)))
(apply 'command (append '("pline") coords '("c")))
(setq currobj (ssadd (entlast) currobj))
(setq coords (list 
(list 959.4375 -167.497) 
(list 885.415 -166.947) 
(list 885.415 -167.124) 
(list 959.4375 -167.574)))
(apply 'command (append '("pline") coords '("c")))
(setq currobj (ssadd (entlast) currobj))
(setq coords (list 
(list 959.4375 -167.717) 
(list 885.415 -167.267) 
(list 885.415 -167.444) 
(list 959.4375 -167.794)))
(apply 'command (append '("pline") coords '("c")))
(setq currobj (ssadd (entlast) currobj))
(setq coords (list 
(list 959.4375 -167.937) 
(list 885.415 -167.587) 
(list 885.415 -167.764) 
(list 959.4375 -168.014)))
(apply 'command (append '("pline") coords '("c")))
(setq currobj (ssadd (entlast) currobj))
(setq coords (list 
(list 959.4375 -168.157) 
(list 885.415 -167.907) 
(list 885.415 -168.084) 
(list 959.4375 -168.234)))
(apply 'command (append '("pline") coords '("c")))
(setq currobj (ssadd (entlast) currobj))
(setq coords (list 
(list 959.4375 -168.377) 
(list 885.415 -168.227) 
(list 885.415 -168.404) 
(list 959.4375 -168.454)))
(apply 'command (append '("pline") coords '("c")))
(setq currobj (ssadd (entlast) currobj))
(setq coords (list 
(list 959.4375 -168.597) 
(list 885.415 -168.547) 
(list 885.415 -168.724) 
(list 959.4375 -168.674)))
(apply 'command (append '("pline") coords '("c")))
(setq currobj (ssadd (entlast) currobj))
(setq coords (list 
(list 959.4375 -168.817) 
(list 885.415 -168.867) 
(list 885.415 -169.044) 
(list 959.4375 -168.894)))
(apply 'command (append '("pline") coords '("c")))
(setq currobj (ssadd (entlast) currobj))
(setq coords (list 
(list 959.4375 -169.037) 
(list 885.415 -169.187) 
(list 885.415 -169.364) 
(list 959.4375 -169.114)))
(apply 'command (append '("pline") coords '("c")))
(setq currobj (ssadd (entlast) currobj))
(setq coords (list 
(list 959.4375 -169.257) 
(list 885.415 -169.507) 
(list 885.415 -169.684) 
(list 959.4375 -169.334)))
(apply 'command (append '("pline") coords '("c")))
(setq currobj (ssadd (entlast) currobj))
(setq coords (list 
(list 959.4375 -169.477) 
(list 885.415 -169.827) 
(list 885.415 -170.004) 
(list 959.4375 -169.554)))
(apply 'command (append '("pline") coords '("c")))
(setq currobj (ssadd (entlast) currobj))
(setq coords (list 
(list 959.4375 -169.697) 
(list 885.415 -170.147) 
(list 885.415 -170.324) 
(list 959.4375 -169.774)))
(apply 'command (append '("pline") coords '("c")))
(setq currobj (ssadd (entlast) currobj))
(setq coords (list 
(list 959.4375 -169.917) 
(list 885.415 -170.467) 
(list 885.415 -170.644) 
(list 959.4375 -169.994)))
(apply 'command (append '("pline") coords '("c")))
(setq currobj (ssadd (entlast) currobj))
(setq coords (list 
(list 959.4375 -170.137) 
(list 885.415 -170.787) 
(list 885.415 -170.964) 
(list 959.4375 -170.214)))
(apply 'command (append '("pline") coords '("c")))
(setq currobj (ssadd (entlast) currobj))
(command "_layer" "set" "nitride" "")
(command "_layer" "set" "text" "")
(command "_circle" "959.0625,-181.357" "0.075")
(command "_circle" "959.0625,-181.057" "0.075")
(command "_circle" "959.0625,-180.757" "0.075")
(command "_circle" "959.0625,-180.457" "0.075")
(command "_circle" "959.0625,-180.157" "0.075")
(command "_circle" "958.7625,-181.357" "0.075")
(command "_circle" "958.7625,-181.057" "0.075")
(command "_circle" "958.7625,-180.757" "0.075")
(command "_circle" "958.7625,-180.457" "0.075")
(command "_circle" "958.7625,-180.157" "0.075")
(command "_circle" "958.4625,-181.357" "0.075")
(command "_circle" "958.4625,-181.057" "0.075")
(command "_circle" "958.4625,-180.757" "0.075")
(command "_circle" "958.4625,-180.457" "0.075")
(command "_circle" "958.4625,-180.157" "0.075")
(command "_circle" "958.1625,-181.357" "0.075")
(command "_circle" "958.1625,-181.057" "0.075")
(command "_circle" "958.1625,-180.757" "0.075")
(command "_circle" "958.1625,-180.457" "0.075")
(command "_circle" "958.1625,-180.157" "0.075")
(command "_circle" "957.8625,-181.357" "0.075")
(command "_circle" "957.8625,-181.057" "0.075")
(command "_circle" "957.8625,-180.757" "0.075")
(command "_circle" "957.8625,-180.457" "0.075")
(command "_circle" "957.8625,-180.157" "0.075")
(command "_layer" "set" "nitride" "")
(setq coords (list 
(list 960.2625 -155.914) 
(list 960.2625 -40.2693) 
(list 959.7375 -40.2693) 
(list 959.7375 -155.914)))
(apply 'command (append '("pline") coords '("c")))
(setq currobj (ssadd (entlast) currobj))
(command "_layer" "set" "prebias" "")
(command "_rectangle" "959.7375,-155.914" "960.2625,-40.2693")
(setq currobj (ssadd (entlast) currobj))
(command "_layer" "set" "nitride" "")
(setq coords (list 
(list 960.2625 -40.2693) 
(list 960.5625 -30.2693) 
(list 960.5625 -30.2693) 
(list 960.5625 -29.2693) 
(list 1034.585 -30.0193) 
(list 1034.585 -25.0763) 
(list 960.5625 -25.8263) 
(list 960.5625 -24.8263) 
(list 960.5625 -24.8263) 
(list 960.2625 -14.8263) 
(list 959.7375 -14.8263) 
(list 959.4375 -24.8263) 
(list 959.4375 -24.8263) 
(list 959.4375 -25.8263) 
(list 885.415 -25.0763) 
(list 885.415 -30.0193) 
(list 959.4375 -29.2693) 
(list 959.4375 -30.2693) 
(list 959.4375 -30.2693) 
(list 959.7375 -40.2693)))
(apply 'command (append '("pline") coords '("c")))
(setq currobj (ssadd (entlast) currobj))
(command "_layer" "set" "prebias" "")
(setq coords (list 
(list 959.4375 -40.2693) 
(list 959.4375 -29.2693) 
(list 885.415 -30.0193) 
(list 885.415 -25.0763) 
(list 959.4375 -25.8263) 
(list 959.4375 -14.8263) 
(list 960.5625 -14.8263) 
(list 960.5625 -25.8263) 
(list 1034.585 -25.0763) 
(list 1034.585 -30.0193) 
(list 960.5625 -29.2693) 
(list 960.5625 -40.2693)))
(apply 'command (append '("pline") coords '("c")))
(setq currobj (ssadd (entlast) currobj))
(command "_layer" "set" "nitride" "")
(command "_layer" "set" "fda1" "")
(setq coords (list 
(list 960.5625 -29.1263) 
(list 1034.585 -29.8763) 
(list 1034.585 -29.6993) 
(list 960.5625 -29.0493)))
(apply 'command (append '("pline") coords '("c")))
(setq currobj (ssadd (entlast) currobj))
(setq coords (list 
(list 960.5625 -28.9063) 
(list 1034.585 -29.5563) 
(list 1034.585 -29.3793) 
(list 960.5625 -28.8293)))
(apply 'command (append '("pline") coords '("c")))
(setq currobj (ssadd (entlast) currobj))
(setq coords (list 
(list 960.5625 -28.6863) 
(list 1034.585 -29.2363) 
(list 1034.585 -29.0593) 
(list 960.5625 -28.6093)))
(apply 'command (append '("pline") coords '("c")))
(setq currobj (ssadd (entlast) currobj))
(setq coords (list 
(list 960.5625 -28.4663) 
(list 1034.585 -28.9163) 
(list 1034.585 -28.7393) 
(list 960.5625 -28.3893)))
(apply 'command (append '("pline") coords '("c")))
(setq currobj (ssadd (entlast) currobj))
(setq coords (list 
(list 960.5625 -28.2463) 
(list 1034.585 -28.5963) 
(list 1034.585 -28.4193) 
(list 960.5625 -28.1693)))
(apply 'command (append '("pline") coords '("c")))
(setq currobj (ssadd (entlast) currobj))
(setq coords (list 
(list 960.5625 -28.0263) 
(list 1034.585 -28.2763) 
(list 1034.585 -28.0993) 
(list 960.5625 -27.9493)))
(apply 'command (append '("pline") coords '("c")))
(setq currobj (ssadd (entlast) currobj))
(setq coords (list 
(list 960.5625 -27.8063) 
(list 1034.585 -27.9563) 
(list 1034.585 -27.7793) 
(list 960.5625 -27.7293)))
(apply 'command (append '("pline") coords '("c")))
(setq currobj (ssadd (entlast) currobj))
(setq coords (list 
(list 960.5625 -27.5863) 
(list 1034.585 -27.6363) 
(list 1034.585 -27.4593) 
(list 960.5625 -27.5093)))
(apply 'command (append '("pline") coords '("c")))
(setq currobj (ssadd (entlast) currobj))
(setq coords (list 
(list 960.5625 -27.3663) 
(list 1034.585 -27.3163) 
(list 1034.585 -27.1393) 
(list 960.5625 -27.2893)))
(apply 'command (append '("pline") coords '("c")))
(setq currobj (ssadd (entlast) currobj))
(setq coords (list 
(list 960.5625 -27.1463) 
(list 1034.585 -26.9963) 
(list 1034.585 -26.8193) 
(list 960.5625 -27.0693)))
(apply 'command (append '("pline") coords '("c")))
(setq currobj (ssadd (entlast) currobj))
(setq coords (list 
(list 960.5625 -26.9263) 
(list 1034.585 -26.6763) 
(list 1034.585 -26.4993) 
(list 960.5625 -26.8493)))
(apply 'command (append '("pline") coords '("c")))
(setq currobj (ssadd (entlast) currobj))
(setq coords (list 
(list 960.5625 -26.7063) 
(list 1034.585 -26.3563) 
(list 1034.585 -26.1793) 
(list 960.5625 -26.6293)))
(apply 'command (append '("pline") coords '("c")))
(setq currobj (ssadd (entlast) currobj))
(setq coords (list 
(list 960.5625 -26.4863) 
(list 1034.585 -26.0363) 
(list 1034.585 -25.8593) 
(list 960.5625 -26.4093)))
(apply 'command (append '("pline") coords '("c")))
(setq currobj (ssadd (entlast) currobj))
(setq coords (list 
(list 960.5625 -26.2663) 
(list 1034.585 -25.7163) 
(list 1034.585 -25.5393) 
(list 960.5625 -26.1893)))
(apply 'command (append '("pline") coords '("c")))
(setq currobj (ssadd (entlast) currobj))
(setq coords (list 
(list 960.5625 -26.0463) 
(list 1034.585 -25.3963) 
(list 1034.585 -25.2193) 
(list 960.5625 -25.9693)))
(apply 'command (append '("pline") coords '("c")))
(setq currobj (ssadd (entlast) currobj))
(setq coords (list 
(list 959.4375 -25.9693) 
(list 885.415 -25.2193) 
(list 885.415 -25.3963) 
(list 959.4375 -26.0463)))
(apply 'command (append '("pline") coords '("c")))
(setq currobj (ssadd (entlast) currobj))
(setq coords (list 
(list 959.4375 -26.1893) 
(list 885.415 -25.5393) 
(list 885.415 -25.7163) 
(list 959.4375 -26.2663)))
(apply 'command (append '("pline") coords '("c")))
(setq currobj (ssadd (entlast) currobj))
(setq coords (list 
(list 959.4375 -26.4093) 
(list 885.415 -25.8593) 
(list 885.415 -26.0363) 
(list 959.4375 -26.4863)))
(apply 'command (append '("pline") coords '("c")))
(setq currobj (ssadd (entlast) currobj))
(setq coords (list 
(list 959.4375 -26.6293) 
(list 885.415 -26.1793) 
(list 885.415 -26.3563) 
(list 959.4375 -26.7063)))
(apply 'command (append '("pline") coords '("c")))
(setq currobj (ssadd (entlast) currobj))
(setq coords (list 
(list 959.4375 -26.8493) 
(list 885.415 -26.4993) 
(list 885.415 -26.6763) 
(list 959.4375 -26.9263)))
(apply 'command (append '("pline") coords '("c")))
(setq currobj (ssadd (entlast) currobj))
(setq coords (list 
(list 959.4375 -27.0693) 
(list 885.415 -26.8193) 
(list 885.415 -26.9963) 
(list 959.4375 -27.1463)))
(apply 'command (append '("pline") coords '("c")))
(setq currobj (ssadd (entlast) currobj))
(setq coords (list 
(list 959.4375 -27.2893) 
(list 885.415 -27.1393) 
(list 885.415 -27.3163) 
(list 959.4375 -27.3663)))
(apply 'command (append '("pline") coords '("c")))
(setq currobj (ssadd (entlast) currobj))
(setq coords (list 
(list 959.4375 -27.5093) 
(list 885.415 -27.4593) 
(list 885.415 -27.6363) 
(list 959.4375 -27.5863)))
(apply 'command (append '("pline") coords '("c")))
(setq currobj (ssadd (entlast) currobj))
(setq coords (list 
(list 959.4375 -27.7293) 
(list 885.415 -27.7793) 
(list 885.415 -27.9563) 
(list 959.4375 -27.8063)))
(apply 'command (append '("pline") coords '("c")))
(setq currobj (ssadd (entlast) currobj))
(setq coords (list 
(list 959.4375 -27.9493) 
(list 885.415 -28.0993) 
(list 885.415 -28.2763) 
(list 959.4375 -28.0263)))
(apply 'command (append '("pline") coords '("c")))
(setq currobj (ssadd (entlast) currobj))
(setq coords (list 
(list 959.4375 -28.1693) 
(list 885.415 -28.4193) 
(list 885.415 -28.5963) 
(list 959.4375 -28.2463)))
(apply 'command (append '("pline") coords '("c")))
(setq currobj (ssadd (entlast) currobj))
(setq coords (list 
(list 959.4375 -28.3893) 
(list 885.415 -28.7393) 
(list 885.415 -28.9163) 
(list 959.4375 -28.4663)))
(apply 'command (append '("pline") coords '("c")))
(setq currobj (ssadd (entlast) currobj))
(setq coords (list 
(list 959.4375 -28.6093) 
(list 885.415 -29.0593) 
(list 885.415 -29.2363) 
(list 959.4375 -28.6863)))
(apply 'command (append '("pline") coords '("c")))
(setq currobj (ssadd (entlast) currobj))
(setq coords (list 
(list 959.4375 -28.8293) 
(list 885.415 -29.3793) 
(list 885.415 -29.5563) 
(list 959.4375 -28.9063)))
(apply 'command (append '("pline") coords '("c")))
(setq currobj (ssadd (entlast) currobj))
(setq coords (list 
(list 959.4375 -29.0493) 
(list 885.415 -29.6993) 
(list 885.415 -29.8763) 
(list 959.4375 -29.1263)))
(apply 'command (append '("pline") coords '("c")))
(setq currobj (ssadd (entlast) currobj))
(command "_layer" "set" "nitride" "")
(command "_layer" "set" "text" "")
(command "_circle" "959.0625,-40.2693" "0.075")
(command "_circle" "959.0625,-39.9693" "0.075")
(command "_circle" "959.0625,-39.6693" "0.075")
(command "_circle" "959.0625,-39.3693" "0.075")
(command "_circle" "959.0625,-39.0693" "0.075")
(command "_circle" "958.7625,-40.2693" "0.075")
(command "_circle" "958.7625,-39.9693" "0.075")
(command "_circle" "958.7625,-39.6693" "0.075")
(command "_circle" "958.7625,-39.3693" "0.075")
(command "_circle" "958.7625,-39.0693" "0.075")
(command "_circle" "958.4625,-40.2693" "0.075")
(command "_circle" "958.4625,-39.9693" "0.075")
(command "_circle" "958.4625,-39.6693" "0.075")
(command "_circle" "958.4625,-39.3693" "0.075")
(command "_circle" "958.4625,-39.0693" "0.075")
(command "_circle" "958.1625,-40.2693" "0.075")
(command "_circle" "958.1625,-39.9693" "0.075")
(command "_circle" "958.1625,-39.6693" "0.075")
(command "_circle" "958.1625,-39.3693" "0.075")
(command "_circle" "958.1625,-39.0693" "0.075")
(command "_circle" "957.8625,-40.2693" "0.075")
(command "_circle" "957.8625,-39.9693" "0.075")
(command "_circle" "957.8625,-39.6693" "0.075")
(command "_circle" "957.8625,-39.3693" "0.075")
(command "_circle" "957.8625,-39.0693" "0.075")
(command "_layer" "set" "nitride" "")
(setq coords (list 
(list 960.2625 -14.8263) 
(list 960.2625 100.8184) 
(list 959.7375 100.8184) 
(list 959.7375 -14.8263)))
(apply 'command (append '("pline") coords '("c")))
(setq currobj (ssadd (entlast) currobj))
(command "_layer" "set" "prebias" "")
(command "_rectangle" "959.7375,-14.8263" "960.2625,100.8184")
(setq currobj (ssadd (entlast) currobj))
(command "_layer" "set" "nitride" "")
(setq coords (list 
(list 960.2625 100.8184) 
(list 960.5625 110.8184) 
(list 960.5625 110.8184) 
(list 960.5625 111.8184) 
(list 1034.585 111.0684) 
(list 1034.585 116.0114) 
(list 960.5625 115.2614) 
(list 960.5625 116.2614) 
(list 960.5625 116.2614) 
(list 960.2625 126.2614) 
(list 959.7375 126.2614) 
(list 959.4375 116.2614) 
(list 959.4375 116.2614) 
(list 959.4375 115.2614) 
(list 885.415 116.0114) 
(list 885.415 111.0684) 
(list 959.4375 111.8184) 
(list 959.4375 110.8184) 
(list 959.4375 110.8184) 
(list 959.7375 100.8184)))
(apply 'command (append '("pline") coords '("c")))
(setq currobj (ssadd (entlast) currobj))
(command "_layer" "set" "prebias" "")
(setq coords (list 
(list 959.4375 100.8184) 
(list 959.4375 111.8184) 
(list 885.415 111.0684) 
(list 885.415 116.0114) 
(list 959.4375 115.2614) 
(list 959.4375 126.2614) 
(list 960.5625 126.2614) 
(list 960.5625 115.2614) 
(list 1034.585 116.0114) 
(list 1034.585 111.0684) 
(list 960.5625 111.8184) 
(list 960.5625 100.8184)))
(apply 'command (append '("pline") coords '("c")))
(setq currobj (ssadd (entlast) currobj))
(command "_layer" "set" "nitride" "")
(command "_layer" "set" "fda1" "")
(setq coords (list 
(list 960.5625 111.9614) 
(list 1034.585 111.2114) 
(list 1034.585 111.3884) 
(list 960.5625 112.0384)))
(apply 'command (append '("pline") coords '("c")))
(setq currobj (ssadd (entlast) currobj))
(setq coords (list 
(list 960.5625 112.1814) 
(list 1034.585 111.5314) 
(list 1034.585 111.7084) 
(list 960.5625 112.2584)))
(apply 'command (append '("pline") coords '("c")))
(setq currobj (ssadd (entlast) currobj))
(setq coords (list 
(list 960.5625 112.4014) 
(list 1034.585 111.8514) 
(list 1034.585 112.0284) 
(list 960.5625 112.4784)))
(apply 'command (append '("pline") coords '("c")))
(setq currobj (ssadd (entlast) currobj))
(setq coords (list 
(list 960.5625 112.6214) 
(list 1034.585 112.1714) 
(list 1034.585 112.3484) 
(list 960.5625 112.6984)))
(apply 'command (append '("pline") coords '("c")))
(setq currobj (ssadd (entlast) currobj))
(setq coords (list 
(list 960.5625 112.8414) 
(list 1034.585 112.4914) 
(list 1034.585 112.6684) 
(list 960.5625 112.9184)))
(apply 'command (append '("pline") coords '("c")))
(setq currobj (ssadd (entlast) currobj))
(setq coords (list 
(list 960.5625 113.0614) 
(list 1034.585 112.8114) 
(list 1034.585 112.9884) 
(list 960.5625 113.1384)))
(apply 'command (append '("pline") coords '("c")))
(setq currobj (ssadd (entlast) currobj))
(setq coords (list 
(list 960.5625 113.2814) 
(list 1034.585 113.1314) 
(list 1034.585 113.3084) 
(list 960.5625 113.3584)))
(apply 'command (append '("pline") coords '("c")))
(setq currobj (ssadd (entlast) currobj))
(setq coords (list 
(list 960.5625 113.5014) 
(list 1034.585 113.4514) 
(list 1034.585 113.6284) 
(list 960.5625 113.5784)))
(apply 'command (append '("pline") coords '("c")))
(setq currobj (ssadd (entlast) currobj))
(setq coords (list 
(list 960.5625 113.7214) 
(list 1034.585 113.7714) 
(list 1034.585 113.9484) 
(list 960.5625 113.7984)))
(apply 'command (append '("pline") coords '("c")))
(setq currobj (ssadd (entlast) currobj))
(setq coords (list 
(list 960.5625 113.9414) 
(list 1034.585 114.0914) 
(list 1034.585 114.2684) 
(list 960.5625 114.0184)))
(apply 'command (append '("pline") coords '("c")))
(setq currobj (ssadd (entlast) currobj))
(setq coords (list 
(list 960.5625 114.1614) 
(list 1034.585 114.4114) 
(list 1034.585 114.5884) 
(list 960.5625 114.2384)))
(apply 'command (append '("pline") coords '("c")))
(setq currobj (ssadd (entlast) currobj))
(setq coords (list 
(list 960.5625 114.3814) 
(list 1034.585 114.7314) 
(list 1034.585 114.9084) 
(list 960.5625 114.4584)))
(apply 'command (append '("pline") coords '("c")))
(setq currobj (ssadd (entlast) currobj))
(setq coords (list 
(list 960.5625 114.6014) 
(list 1034.585 115.0514) 
(list 1034.585 115.2284) 
(list 960.5625 114.6784)))
(apply 'command (append '("pline") coords '("c")))
(setq currobj (ssadd (entlast) currobj))
(setq coords (list 
(list 960.5625 114.8214) 
(list 1034.585 115.3714) 
(list 1034.585 115.5484) 
(list 960.5625 114.8984)))
(apply 'command (append '("pline") coords '("c")))
(setq currobj (ssadd (entlast) currobj))
(setq coords (list 
(list 960.5625 115.0414) 
(list 1034.585 115.6914) 
(list 1034.585 115.8684) 
(list 960.5625 115.1184)))
(apply 'command (append '("pline") coords '("c")))
(setq currobj (ssadd (entlast) currobj))
(setq coords (list 
(list 959.4375 115.1184) 
(list 885.415 115.8684) 
(list 885.415 115.6914) 
(list 959.4375 115.0414)))
(apply 'command (append '("pline") coords '("c")))
(setq currobj (ssadd (entlast) currobj))
(setq coords (list 
(list 959.4375 114.8984) 
(list 885.415 115.5484) 
(list 885.415 115.3714) 
(list 959.4375 114.8214)))
(apply 'command (append '("pline") coords '("c")))
(setq currobj (ssadd (entlast) currobj))
(setq coords (list 
(list 959.4375 114.6784) 
(list 885.415 115.2284) 
(list 885.415 115.0514) 
(list 959.4375 114.6014)))
(apply 'command (append '("pline") coords '("c")))
(setq currobj (ssadd (entlast) currobj))
(setq coords (list 
(list 959.4375 114.4584) 
(list 885.415 114.9084) 
(list 885.415 114.7314) 
(list 959.4375 114.3814)))
(apply 'command (append '("pline") coords '("c")))
(setq currobj (ssadd (entlast) currobj))
(setq coords (list 
(list 959.4375 114.2384) 
(list 885.415 114.5884) 
(list 885.415 114.4114) 
(list 959.4375 114.1614)))
(apply 'command (append '("pline") coords '("c")))
(setq currobj (ssadd (entlast) currobj))
(setq coords (list 
(list 959.4375 114.0184) 
(list 885.415 114.2684) 
(list 885.415 114.0914) 
(list 959.4375 113.9414)))
(apply 'command (append '("pline") coords '("c")))
(setq currobj (ssadd (entlast) currobj))
(setq coords (list 
(list 959.4375 113.7984) 
(list 885.415 113.9484) 
(list 885.415 113.7714) 
(list 959.4375 113.7214)))
(apply 'command (append '("pline") coords '("c")))
(setq currobj (ssadd (entlast) currobj))
(setq coords (list 
(list 959.4375 113.5784) 
(list 885.415 113.6284) 
(list 885.415 113.4514) 
(list 959.4375 113.5014)))
(apply 'command (append '("pline") coords '("c")))
(setq currobj (ssadd (entlast) currobj))
(setq coords (list 
(list 959.4375 113.3584) 
(list 885.415 113.3084) 
(list 885.415 113.1314) 
(list 959.4375 113.2814)))
(apply 'command (append '("pline") coords '("c")))
(setq currobj (ssadd (entlast) currobj))
(setq coords (list 
(list 959.4375 113.1384) 
(list 885.415 112.9884) 
(list 885.415 112.8114) 
(list 959.4375 113.0614)))
(apply 'command (append '("pline") coords '("c")))
(setq currobj (ssadd (entlast) currobj))
(setq coords (list 
(list 959.4375 112.9184) 
(list 885.415 112.6684) 
(list 885.415 112.4914) 
(list 959.4375 112.8414)))
(apply 'command (append '("pline") coords '("c")))
(setq currobj (ssadd (entlast) currobj))
(setq coords (list 
(list 959.4375 112.6984) 
(list 885.415 112.3484) 
(list 885.415 112.1714) 
(list 959.4375 112.6214)))
(apply 'command (append '("pline") coords '("c")))
(setq currobj (ssadd (entlast) currobj))
(setq coords (list 
(list 959.4375 112.4784) 
(list 885.415 112.0284) 
(list 885.415 111.8514) 
(list 959.4375 112.4014)))
(apply 'command (append '("pline") coords '("c")))
(setq currobj (ssadd (entlast) currobj))
(setq coords (list 
(list 959.4375 112.2584) 
(list 885.415 111.7084) 
(list 885.415 111.5314) 
(list 959.4375 112.1814)))
(apply 'command (append '("pline") coords '("c")))
(setq currobj (ssadd (entlast) currobj))
(setq coords (list 
(list 959.4375 112.0384) 
(list 885.415 111.3884) 
(list 885.415 111.2114) 
(list 959.4375 111.9614)))
(apply 'command (append '("pline") coords '("c")))
(setq currobj (ssadd (entlast) currobj))
(command "_layer" "set" "nitride" "")
(command "_layer" "set" "text" "")
(command "_circle" "959.0625,100.8184" "0.075")
(command "_circle" "959.0625,101.1184" "0.075")
(command "_circle" "959.0625,101.4184" "0.075")
(command "_circle" "959.0625,101.7184" "0.075")
(command "_circle" "959.0625,102.0184" "0.075")
(command "_circle" "958.7625,100.8184" "0.075")
(command "_circle" "958.7625,101.1184" "0.075")
(command "_circle" "958.7625,101.4184" "0.075")
(command "_circle" "958.7625,101.7184" "0.075")
(command "_circle" "958.7625,102.0184" "0.075")
(command "_circle" "958.4625,100.8184" "0.075")
(command "_circle" "958.4625,101.1184" "0.075")
(command "_circle" "958.4625,101.4184" "0.075")
(command "_circle" "958.4625,101.7184" "0.075")
(command "_circle" "958.4625,102.0184" "0.075")
(command "_circle" "958.1625,100.8184" "0.075")
(command "_circle" "958.1625,101.1184" "0.075")
(command "_circle" "958.1625,101.4184" "0.075")
(command "_circle" "958.1625,101.7184" "0.075")
(command "_circle" "958.1625,102.0184" "0.075")
(command "_circle" "957.8625,100.8184" "0.075")
(command "_circle" "957.8625,101.1184" "0.075")
(command "_circle" "957.8625,101.4184" "0.075")
(command "_circle" "957.8625,101.7184" "0.075")
(command "_circle" "957.8625,102.0184" "0.075")
(command "_layer" "set" "nitride" "")
(setq coords (list 
(list 960.2625 126.2614) 
(list 960.2625 241.9061) 
(list 959.7375 241.9061) 
(list 959.7375 126.2614)))
(apply 'command (append '("pline") coords '("c")))
(setq currobj (ssadd (entlast) currobj))
(command "_layer" "set" "prebias" "")
(command "_rectangle" "959.7375,126.2614" "960.2625,241.9061")
(setq currobj (ssadd (entlast) currobj))
(command "_layer" "set" "nitride" "")
(setq coords (list 
(list 960.2625 241.9061) 
(list 960.5625 251.9061) 
(list 960.5625 251.9061) 
(list 960.5625 252.9061) 
(list 1034.585 252.1561) 
(list 1034.585 257.0991) 
(list 960.5625 256.3491) 
(list 960.5625 257.3491) 
(list 960.5625 257.3491) 
(list 960.2625 267.3491) 
(list 959.7375 267.3491) 
(list 959.4375 257.3491) 
(list 959.4375 257.3491) 
(list 959.4375 256.3491) 
(list 885.415 257.0991) 
(list 885.415 252.1561) 
(list 959.4375 252.9061) 
(list 959.4375 251.9061) 
(list 959.4375 251.9061) 
(list 959.7375 241.9061)))
(apply 'command (append '("pline") coords '("c")))
(setq currobj (ssadd (entlast) currobj))
(command "_layer" "set" "prebias" "")
(setq coords (list 
(list 959.4375 241.9061) 
(list 959.4375 252.9061) 
(list 885.415 252.1561) 
(list 885.415 257.0991) 
(list 959.4375 256.3491) 
(list 959.4375 267.3491) 
(list 960.5625 267.3491) 
(list 960.5625 256.3491) 
(list 1034.585 257.0991) 
(list 1034.585 252.1561) 
(list 960.5625 252.9061) 
(list 960.5625 241.9061)))
(apply 'command (append '("pline") coords '("c")))
(setq currobj (ssadd (entlast) currobj))
(command "_layer" "set" "nitride" "")
(command "_layer" "set" "fda1" "")
(setq coords (list 
(list 960.5625 253.0491) 
(list 1034.585 252.2991) 
(list 1034.585 252.4761) 
(list 960.5625 253.1261)))
(apply 'command (append '("pline") coords '("c")))
(setq currobj (ssadd (entlast) currobj))
(setq coords (list 
(list 960.5625 253.2691) 
(list 1034.585 252.6191) 
(list 1034.585 252.7961) 
(list 960.5625 253.3461)))
(apply 'command (append '("pline") coords '("c")))
(setq currobj (ssadd (entlast) currobj))
(setq coords (list 
(list 960.5625 253.4891) 
(list 1034.585 252.9391) 
(list 1034.585 253.1161) 
(list 960.5625 253.5661)))
(apply 'command (append '("pline") coords '("c")))
(setq currobj (ssadd (entlast) currobj))
(setq coords (list 
(list 960.5625 253.7091) 
(list 1034.585 253.2591) 
(list 1034.585 253.4361) 
(list 960.5625 253.7861)))
(apply 'command (append '("pline") coords '("c")))
(setq currobj (ssadd (entlast) currobj))
(setq coords (list 
(list 960.5625 253.9291) 
(list 1034.585 253.5791) 
(list 1034.585 253.7561) 
(list 960.5625 254.0061)))
(apply 'command (append '("pline") coords '("c")))
(setq currobj (ssadd (entlast) currobj))
(setq coords (list 
(list 960.5625 254.1491) 
(list 1034.585 253.8991) 
(list 1034.585 254.0761) 
(list 960.5625 254.2261)))
(apply 'command (append '("pline") coords '("c")))
(setq currobj (ssadd (entlast) currobj))
(setq coords (list 
(list 960.5625 254.3691) 
(list 1034.585 254.2191) 
(list 1034.585 254.3961) 
(list 960.5625 254.4461)))
(apply 'command (append '("pline") coords '("c")))
(setq currobj (ssadd (entlast) currobj))
(setq coords (list 
(list 960.5625 254.5891) 
(list 1034.585 254.5391) 
(list 1034.585 254.7161) 
(list 960.5625 254.6661)))
(apply 'command (append '("pline") coords '("c")))
(setq currobj (ssadd (entlast) currobj))
(setq coords (list 
(list 960.5625 254.8091) 
(list 1034.585 254.8591) 
(list 1034.585 255.0361) 
(list 960.5625 254.8861)))
(apply 'command (append '("pline") coords '("c")))
(setq currobj (ssadd (entlast) currobj))
(setq coords (list 
(list 960.5625 255.0291) 
(list 1034.585 255.1791) 
(list 1034.585 255.3561) 
(list 960.5625 255.1061)))
(apply 'command (append '("pline") coords '("c")))
(setq currobj (ssadd (entlast) currobj))
(setq coords (list 
(list 960.5625 255.2491) 
(list 1034.585 255.4991) 
(list 1034.585 255.6761) 
(list 960.5625 255.3261)))
(apply 'command (append '("pline") coords '("c")))
(setq currobj (ssadd (entlast) currobj))
(setq coords (list 
(list 960.5625 255.4691) 
(list 1034.585 255.8191) 
(list 1034.585 255.9961) 
(list 960.5625 255.5461)))
(apply 'command (append '("pline") coords '("c")))
(setq currobj (ssadd (entlast) currobj))
(setq coords (list 
(list 960.5625 255.6891) 
(list 1034.585 256.1391) 
(list 1034.585 256.3161) 
(list 960.5625 255.7661)))
(apply 'command (append '("pline") coords '("c")))
(setq currobj (ssadd (entlast) currobj))
(setq coords (list 
(list 960.5625 255.9091) 
(list 1034.585 256.4591) 
(list 1034.585 256.6361) 
(list 960.5625 255.9861)))
(apply 'command (append '("pline") coords '("c")))
(setq currobj (ssadd (entlast) currobj))
(setq coords (list 
(list 960.5625 256.1291) 
(list 1034.585 256.7791) 
(list 1034.585 256.9561) 
(list 960.5625 256.2061)))
(apply 'command (append '("pline") coords '("c")))
(setq currobj (ssadd (entlast) currobj))
(setq coords (list 
(list 959.4375 256.2061) 
(list 885.415 256.9561) 
(list 885.415 256.7791) 
(list 959.4375 256.1291)))
(apply 'command (append '("pline") coords '("c")))
(setq currobj (ssadd (entlast) currobj))
(setq coords (list 
(list 959.4375 255.9861) 
(list 885.415 256.6361) 
(list 885.415 256.4591) 
(list 959.4375 255.9091)))
(apply 'command (append '("pline") coords '("c")))
(setq currobj (ssadd (entlast) currobj))
(setq coords (list 
(list 959.4375 255.7661) 
(list 885.415 256.3161) 
(list 885.415 256.1391) 
(list 959.4375 255.6891)))
(apply 'command (append '("pline") coords '("c")))
(setq currobj (ssadd (entlast) currobj))
(setq coords (list 
(list 959.4375 255.5461) 
(list 885.415 255.9961) 
(list 885.415 255.8191) 
(list 959.4375 255.4691)))
(apply 'command (append '("pline") coords '("c")))
(setq currobj (ssadd (entlast) currobj))
(setq coords (list 
(list 959.4375 255.3261) 
(list 885.415 255.6761) 
(list 885.415 255.4991) 
(list 959.4375 255.2491)))
(apply 'command (append '("pline") coords '("c")))
(setq currobj (ssadd (entlast) currobj))
(setq coords (list 
(list 959.4375 255.1061) 
(list 885.415 255.3561) 
(list 885.415 255.1791) 
(list 959.4375 255.0291)))
(apply 'command (append '("pline") coords '("c")))
(setq currobj (ssadd (entlast) currobj))
(setq coords (list 
(list 959.4375 254.8861) 
(list 885.415 255.0361) 
(list 885.415 254.8591) 
(list 959.4375 254.8091)))
(apply 'command (append '("pline") coords '("c")))
(setq currobj (ssadd (entlast) currobj))
(setq coords (list 
(list 959.4375 254.6661) 
(list 885.415 254.7161) 
(list 885.415 254.5391) 
(list 959.4375 254.5891)))
(apply 'command (append '("pline") coords '("c")))
(setq currobj (ssadd (entlast) currobj))
(setq coords (list 
(list 959.4375 254.4461) 
(list 885.415 254.3961) 
(list 885.415 254.2191) 
(list 959.4375 254.3691)))
(apply 'command (append '("pline") coords '("c")))
(setq currobj (ssadd (entlast) currobj))
(setq coords (list 
(list 959.4375 254.2261) 
(list 885.415 254.0761) 
(list 885.415 253.8991) 
(list 959.4375 254.1491)))
(apply 'command (append '("pline") coords '("c")))
(setq currobj (ssadd (entlast) currobj))
(setq coords (list 
(list 959.4375 254.0061) 
(list 885.415 253.7561) 
(list 885.415 253.5791) 
(list 959.4375 253.9291)))
(apply 'command (append '("pline") coords '("c")))
(setq currobj (ssadd (entlast) currobj))
(setq coords (list 
(list 959.4375 253.7861) 
(list 885.415 253.4361) 
(list 885.415 253.2591) 
(list 959.4375 253.7091)))
(apply 'command (append '("pline") coords '("c")))
(setq currobj (ssadd (entlast) currobj))
(setq coords (list 
(list 959.4375 253.5661) 
(list 885.415 253.1161) 
(list 885.415 252.9391) 
(list 959.4375 253.4891)))
(apply 'command (append '("pline") coords '("c")))
(setq currobj (ssadd (entlast) currobj))
(setq coords (list 
(list 959.4375 253.3461) 
(list 885.415 252.7961) 
(list 885.415 252.6191) 
(list 959.4375 253.2691)))
(apply 'command (append '("pline") coords '("c")))
(setq currobj (ssadd (entlast) currobj))
(setq coords (list 
(list 959.4375 253.1261) 
(list 885.415 252.4761) 
(list 885.415 252.2991) 
(list 959.4375 253.0491)))
(apply 'command (append '("pline") coords '("c")))
(setq currobj (ssadd (entlast) currobj))
(command "_layer" "set" "nitride" "")
(command "_layer" "set" "text" "")
(command "_circle" "959.0625,241.9061" "0.075")
(command "_circle" "959.0625,242.2061" "0.075")
(command "_circle" "959.0625,242.5061" "0.075")
(command "_circle" "959.0625,242.8061" "0.075")
(command "_circle" "959.0625,243.1061" "0.075")
(command "_circle" "958.7625,241.9061" "0.075")
(command "_circle" "958.7625,242.2061" "0.075")
(command "_circle" "958.7625,242.5061" "0.075")
(command "_circle" "958.7625,242.8061" "0.075")
(command "_circle" "958.7625,243.1061" "0.075")
(command "_circle" "958.4625,241.9061" "0.075")
(command "_circle" "958.4625,242.2061" "0.075")
(command "_circle" "958.4625,242.5061" "0.075")
(command "_circle" "958.4625,242.8061" "0.075")
(command "_circle" "958.4625,243.1061" "0.075")
(command "_circle" "958.1625,241.9061" "0.075")
(command "_circle" "958.1625,242.2061" "0.075")
(command "_circle" "958.1625,242.5061" "0.075")
(command "_circle" "958.1625,242.8061" "0.075")
(command "_circle" "958.1625,243.1061" "0.075")
(command "_circle" "957.8625,241.9061" "0.075")
(command "_circle" "957.8625,242.2061" "0.075")
(command "_circle" "957.8625,242.5061" "0.075")
(command "_circle" "957.8625,242.8061" "0.075")
(command "_circle" "957.8625,243.1061" "0.075")
(command "_layer" "set" "nitride" "")
(setq coords (list 
(list 960.2625 267.3491) 
(list 960.2625 382.9939) 
(list 959.7375 382.9939) 
(list 959.7375 267.3491)))
(apply 'command (append '("pline") coords '("c")))
(setq currobj (ssadd (entlast) currobj))
(command "_layer" "set" "prebias" "")
(command "_rectangle" "959.7375,267.3491" "960.2625,382.9939")
(setq currobj (ssadd (entlast) currobj))
(command "_layer" "set" "nitride" "")
(setq coords (list 
(list 960.2625 382.9939) 
(list 960.5625 392.9939) 
(list 960.5625 392.9939) 
(list 960.5625 393.9939) 
(list 1034.585 393.2439) 
(list 1034.585 398.1869) 
(list 960.5625 397.4369) 
(list 960.5625 398.4369) 
(list 960.5625 398.4369) 
(list 960.2625 408.4369) 
(list 959.7375 408.4369) 
(list 959.4375 398.4369) 
(list 959.4375 398.4369) 
(list 959.4375 397.4369) 
(list 885.415 398.1869) 
(list 885.415 393.2439) 
(list 959.4375 393.9939) 
(list 959.4375 392.9939) 
(list 959.4375 392.9939) 
(list 959.7375 382.9939)))
(apply 'command (append '("pline") coords '("c")))
(setq currobj (ssadd (entlast) currobj))
(command "_layer" "set" "prebias" "")
(setq coords (list 
(list 959.4375 382.9939) 
(list 959.4375 393.9939) 
(list 885.415 393.2439) 
(list 885.415 398.1869) 
(list 959.4375 397.4369) 
(list 959.4375 408.4369) 
(list 960.5625 408.4369) 
(list 960.5625 397.4369) 
(list 1034.585 398.1869) 
(list 1034.585 393.2439) 
(list 960.5625 393.9939) 
(list 960.5625 382.9939)))
(apply 'command (append '("pline") coords '("c")))
(setq currobj (ssadd (entlast) currobj))
(command "_layer" "set" "nitride" "")
(command "_layer" "set" "fda1" "")
(setq coords (list 
(list 960.5625 394.1369) 
(list 1034.585 393.3869) 
(list 1034.585 393.5639) 
(list 960.5625 394.2139)))
(apply 'command (append '("pline") coords '("c")))
(setq currobj (ssadd (entlast) currobj))
(setq coords (list 
(list 960.5625 394.3569) 
(list 1034.585 393.7069) 
(list 1034.585 393.8839) 
(list 960.5625 394.4339)))
(apply 'command (append '("pline") coords '("c")))
(setq currobj (ssadd (entlast) currobj))
(setq coords (list 
(list 960.5625 394.5769) 
(list 1034.585 394.0269) 
(list 1034.585 394.2039) 
(list 960.5625 394.6539)))
(apply 'command (append '("pline") coords '("c")))
(setq currobj (ssadd (entlast) currobj))
(setq coords (list 
(list 960.5625 394.7969) 
(list 1034.585 394.3469) 
(list 1034.585 394.5239) 
(list 960.5625 394.8739)))
(apply 'command (append '("pline") coords '("c")))
(setq currobj (ssadd (entlast) currobj))
(setq coords (list 
(list 960.5625 395.0169) 
(list 1034.585 394.6669) 
(list 1034.585 394.8439) 
(list 960.5625 395.0939)))
(apply 'command (append '("pline") coords '("c")))
(setq currobj (ssadd (entlast) currobj))
(setq coords (list 
(list 960.5625 395.2369) 
(list 1034.585 394.9869) 
(list 1034.585 395.1639) 
(list 960.5625 395.3139)))
(apply 'command (append '("pline") coords '("c")))
(setq currobj (ssadd (entlast) currobj))
(setq coords (list 
(list 960.5625 395.4569) 
(list 1034.585 395.3069) 
(list 1034.585 395.4839) 
(list 960.5625 395.5339)))
(apply 'command (append '("pline") coords '("c")))
(setq currobj (ssadd (entlast) currobj))
(setq coords (list 
(list 960.5625 395.6769) 
(list 1034.585 395.6269) 
(list 1034.585 395.8039) 
(list 960.5625 395.7539)))
(apply 'command (append '("pline") coords '("c")))
(setq currobj (ssadd (entlast) currobj))
(setq coords (list 
(list 960.5625 395.8969) 
(list 1034.585 395.9469) 
(list 1034.585 396.1239) 
(list 960.5625 395.9739)))
(apply 'command (append '("pline") coords '("c")))
(setq currobj (ssadd (entlast) currobj))
(setq coords (list 
(list 960.5625 396.1169) 
(list 1034.585 396.2669) 
(list 1034.585 396.4439) 
(list 960.5625 396.1939)))
(apply 'command (append '("pline") coords '("c")))
(setq currobj (ssadd (entlast) currobj))
(setq coords (list 
(list 960.5625 396.3369) 
(list 1034.585 396.5869) 
(list 1034.585 396.7639) 
(list 960.5625 396.4139)))
(apply 'command (append '("pline") coords '("c")))
(setq currobj (ssadd (entlast) currobj))
(setq coords (list 
(list 960.5625 396.5569) 
(list 1034.585 396.9069) 
(list 1034.585 397.0839) 
(list 960.5625 396.6339)))
(apply 'command (append '("pline") coords '("c")))
(setq currobj (ssadd (entlast) currobj))
(setq coords (list 
(list 960.5625 396.7769) 
(list 1034.585 397.2269) 
(list 1034.585 397.4039) 
(list 960.5625 396.8539)))
(apply 'command (append '("pline") coords '("c")))
(setq currobj (ssadd (entlast) currobj))
(setq coords (list 
(list 960.5625 396.9969) 
(list 1034.585 397.5469) 
(list 1034.585 397.7239) 
(list 960.5625 397.0739)))
(apply 'command (append '("pline") coords '("c")))
(setq currobj (ssadd (entlast) currobj))
(setq coords (list 
(list 960.5625 397.2169) 
(list 1034.585 397.8669) 
(list 1034.585 398.0439) 
(list 960.5625 397.2939)))
(apply 'command (append '("pline") coords '("c")))
(setq currobj (ssadd (entlast) currobj))
(setq coords (list 
(list 959.4375 397.2939) 
(list 885.415 398.0439) 
(list 885.415 397.8669) 
(list 959.4375 397.2169)))
(apply 'command (append '("pline") coords '("c")))
(setq currobj (ssadd (entlast) currobj))
(setq coords (list 
(list 959.4375 397.0739) 
(list 885.415 397.7239) 
(list 885.415 397.5469) 
(list 959.4375 396.9969)))
(apply 'command (append '("pline") coords '("c")))
(setq currobj (ssadd (entlast) currobj))
(setq coords (list 
(list 959.4375 396.8539) 
(list 885.415 397.4039) 
(list 885.415 397.2269) 
(list 959.4375 396.7769)))
(apply 'command (append '("pline") coords '("c")))
(setq currobj (ssadd (entlast) currobj))
(setq coords (list 
(list 959.4375 396.6339) 
(list 885.415 397.0839) 
(list 885.415 396.9069) 
(list 959.4375 396.5569)))
(apply 'command (append '("pline") coords '("c")))
(setq currobj (ssadd (entlast) currobj))
(setq coords (list 
(list 959.4375 396.4139) 
(list 885.415 396.7639) 
(list 885.415 396.5869) 
(list 959.4375 396.3369)))
(apply 'command (append '("pline") coords '("c")))
(setq currobj (ssadd (entlast) currobj))
(setq coords (list 
(list 959.4375 396.1939) 
(list 885.415 396.4439) 
(list 885.415 396.2669) 
(list 959.4375 396.1169)))
(apply 'command (append '("pline") coords '("c")))
(setq currobj (ssadd (entlast) currobj))
(setq coords (list 
(list 959.4375 395.9739) 
(list 885.415 396.1239) 
(list 885.415 395.9469) 
(list 959.4375 395.8969)))
(apply 'command (append '("pline") coords '("c")))
(setq currobj (ssadd (entlast) currobj))
(setq coords (list 
(list 959.4375 395.7539) 
(list 885.415 395.8039) 
(list 885.415 395.6269) 
(list 959.4375 395.6769)))
(apply 'command (append '("pline") coords '("c")))
(setq currobj (ssadd (entlast) currobj))
(setq coords (list 
(list 959.4375 395.5339) 
(list 885.415 395.4839) 
(list 885.415 395.3069) 
(list 959.4375 395.4569)))
(apply 'command (append '("pline") coords '("c")))
(setq currobj (ssadd (entlast) currobj))
(setq coords (list 
(list 959.4375 395.3139) 
(list 885.415 395.1639) 
(list 885.415 394.9869) 
(list 959.4375 395.2369)))
(apply 'command (append '("pline") coords '("c")))
(setq currobj (ssadd (entlast) currobj))
(setq coords (list 
(list 959.4375 395.0939) 
(list 885.415 394.8439) 
(list 885.415 394.6669) 
(list 959.4375 395.0169)))
(apply 'command (append '("pline") coords '("c")))
(setq currobj (ssadd (entlast) currobj))
(setq coords (list 
(list 959.4375 394.8739) 
(list 885.415 394.5239) 
(list 885.415 394.3469) 
(list 959.4375 394.7969)))
(apply 'command (append '("pline") coords '("c")))
(setq currobj (ssadd (entlast) currobj))
(setq coords (list 
(list 959.4375 394.6539) 
(list 885.415 394.2039) 
(list 885.415 394.0269) 
(list 959.4375 394.5769)))
(apply 'command (append '("pline") coords '("c")))
(setq currobj (ssadd (entlast) currobj))
(setq coords (list 
(list 959.4375 394.4339) 
(list 885.415 393.8839) 
(list 885.415 393.7069) 
(list 959.4375 394.3569)))
(apply 'command (append '("pline") coords '("c")))
(setq currobj (ssadd (entlast) currobj))
(setq coords (list 
(list 959.4375 394.2139) 
(list 885.415 393.5639) 
(list 885.415 393.3869) 
(list 959.4375 394.1369)))
(apply 'command (append '("pline") coords '("c")))
(setq currobj (ssadd (entlast) currobj))
(command "_layer" "set" "nitride" "")
(command "_layer" "set" "text" "")
(command "_circle" "959.0625,382.9939" "0.075")
(command "_circle" "959.0625,383.2939" "0.075")
(command "_circle" "959.0625,383.5939" "0.075")
(command "_circle" "959.0625,383.8939" "0.075")
(command "_circle" "959.0625,384.1939" "0.075")
(command "_circle" "958.7625,382.9939" "0.075")
(command "_circle" "958.7625,383.2939" "0.075")
(command "_circle" "958.7625,383.5939" "0.075")
(command "_circle" "958.7625,383.8939" "0.075")
(command "_circle" "958.7625,384.1939" "0.075")
(command "_circle" "958.4625,382.9939" "0.075")
(command "_circle" "958.4625,383.2939" "0.075")
(command "_circle" "958.4625,383.5939" "0.075")
(command "_circle" "958.4625,383.8939" "0.075")
(command "_circle" "958.4625,384.1939" "0.075")
(command "_circle" "958.1625,382.9939" "0.075")
(command "_circle" "958.1625,383.2939" "0.075")
(command "_circle" "958.1625,383.5939" "0.075")
(command "_circle" "958.1625,383.8939" "0.075")
(command "_circle" "958.1625,384.1939" "0.075")
(command "_circle" "957.8625,382.9939" "0.075")
(command "_circle" "957.8625,383.2939" "0.075")
(command "_circle" "957.8625,383.5939" "0.075")
(command "_circle" "957.8625,383.8939" "0.075")
(command "_circle" "957.8625,384.1939" "0.075")
(command "_layer" "set" "nitride" "")
(setq coords (list 
(list 960.2625 408.4369) 
(list 960.2625 524.0816) 
(list 959.7375 524.0816) 
(list 959.7375 408.4369)))
(apply 'command (append '("pline") coords '("c")))
(setq currobj (ssadd (entlast) currobj))
(command "_layer" "set" "prebias" "")
(command "_rectangle" "959.7375,408.4369" "960.2625,524.0816")
(setq currobj (ssadd (entlast) currobj))
(command "_layer" "set" "nitride" "")
(setq coords (list 
(list 960.2625 524.0816) 
(list 960.5625 534.0816) 
(list 960.5625 534.0816) 
(list 960.5625 535.0816) 
(list 1034.585 534.3316) 
(list 1034.585 539.2746) 
(list 960.5625 538.5246) 
(list 960.5625 539.5246) 
(list 960.5625 539.5246) 
(list 960.2625 549.5246) 
(list 959.7375 549.5246) 
(list 959.4375 539.5246) 
(list 959.4375 539.5246) 
(list 959.4375 538.5246) 
(list 885.415 539.2746) 
(list 885.415 534.3316) 
(list 959.4375 535.0816) 
(list 959.4375 534.0816) 
(list 959.4375 534.0816) 
(list 959.7375 524.0816)))
(apply 'command (append '("pline") coords '("c")))
(setq currobj (ssadd (entlast) currobj))
(command "_layer" "set" "prebias" "")
(setq coords (list 
(list 959.4375 524.0816) 
(list 959.4375 535.0816) 
(list 885.415 534.3316) 
(list 885.415 539.2746) 
(list 959.4375 538.5246) 
(list 959.4375 549.5246) 
(list 960.5625 549.5246) 
(list 960.5625 538.5246) 
(list 1034.585 539.2746) 
(list 1034.585 534.3316) 
(list 960.5625 535.0816) 
(list 960.5625 524.0816)))
(apply 'command (append '("pline") coords '("c")))
(setq currobj (ssadd (entlast) currobj))
(command "_layer" "set" "nitride" "")
(command "_layer" "set" "fda1" "")
(setq coords (list 
(list 960.5625 535.2246) 
(list 1034.585 534.4746) 
(list 1034.585 534.6516) 
(list 960.5625 535.3016)))
(apply 'command (append '("pline") coords '("c")))
(setq currobj (ssadd (entlast) currobj))
(setq coords (list 
(list 960.5625 535.4446) 
(list 1034.585 534.7946) 
(list 1034.585 534.9716) 
(list 960.5625 535.5216)))
(apply 'command (append '("pline") coords '("c")))
(setq currobj (ssadd (entlast) currobj))
(setq coords (list 
(list 960.5625 535.6646) 
(list 1034.585 535.1146) 
(list 1034.585 535.2916) 
(list 960.5625 535.7416)))
(apply 'command (append '("pline") coords '("c")))
(setq currobj (ssadd (entlast) currobj))
(setq coords (list 
(list 960.5625 535.8846) 
(list 1034.585 535.4346) 
(list 1034.585 535.6116) 
(list 960.5625 535.9616)))
(apply 'command (append '("pline") coords '("c")))
(setq currobj (ssadd (entlast) currobj))
(setq coords (list 
(list 960.5625 536.1046) 
(list 1034.585 535.7546) 
(list 1034.585 535.9316) 
(list 960.5625 536.1816)))
(apply 'command (append '("pline") coords '("c")))
(setq currobj (ssadd (entlast) currobj))
(setq coords (list 
(list 960.5625 536.3246) 
(list 1034.585 536.0746) 
(list 1034.585 536.2516) 
(list 960.5625 536.4016)))
(apply 'command (append '("pline") coords '("c")))
(setq currobj (ssadd (entlast) currobj))
(setq coords (list 
(list 960.5625 536.5446) 
(list 1034.585 536.3946) 
(list 1034.585 536.5716) 
(list 960.5625 536.6216)))
(apply 'command (append '("pline") coords '("c")))
(setq currobj (ssadd (entlast) currobj))
(setq coords (list 
(list 960.5625 536.7646) 
(list 1034.585 536.7146) 
(list 1034.585 536.8916) 
(list 960.5625 536.8416)))
(apply 'command (append '("pline") coords '("c")))
(setq currobj (ssadd (entlast) currobj))
(setq coords (list 
(list 960.5625 536.9846) 
(list 1034.585 537.0346) 
(list 1034.585 537.2116) 
(list 960.5625 537.0616)))
(apply 'command (append '("pline") coords '("c")))
(setq currobj (ssadd (entlast) currobj))
(setq coords (list 
(list 960.5625 537.2046) 
(list 1034.585 537.3546) 
(list 1034.585 537.5316) 
(list 960.5625 537.2816)))
(apply 'command (append '("pline") coords '("c")))
(setq currobj (ssadd (entlast) currobj))
(setq coords (list 
(list 960.5625 537.4246) 
(list 1034.585 537.6746) 
(list 1034.585 537.8516) 
(list 960.5625 537.5016)))
(apply 'command (append '("pline") coords '("c")))
(setq currobj (ssadd (entlast) currobj))
(setq coords (list 
(list 960.5625 537.6446) 
(list 1034.585 537.9946) 
(list 1034.585 538.1716) 
(list 960.5625 537.7216)))
(apply 'command (append '("pline") coords '("c")))
(setq currobj (ssadd (entlast) currobj))
(setq coords (list 
(list 960.5625 537.8646) 
(list 1034.585 538.3146) 
(list 1034.585 538.4916) 
(list 960.5625 537.9416)))
(apply 'command (append '("pline") coords '("c")))
(setq currobj (ssadd (entlast) currobj))
(setq coords (list 
(list 960.5625 538.0846) 
(list 1034.585 538.6346) 
(list 1034.585 538.8116) 
(list 960.5625 538.1616)))
(apply 'command (append '("pline") coords '("c")))
(setq currobj (ssadd (entlast) currobj))
(setq coords (list 
(list 960.5625 538.3046) 
(list 1034.585 538.9546) 
(list 1034.585 539.1316) 
(list 960.5625 538.3816)))
(apply 'command (append '("pline") coords '("c")))
(setq currobj (ssadd (entlast) currobj))
(setq coords (list 
(list 959.4375 538.3816) 
(list 885.415 539.1316) 
(list 885.415 538.9546) 
(list 959.4375 538.3046)))
(apply 'command (append '("pline") coords '("c")))
(setq currobj (ssadd (entlast) currobj))
(setq coords (list 
(list 959.4375 538.1616) 
(list 885.415 538.8116) 
(list 885.415 538.6346) 
(list 959.4375 538.0846)))
(apply 'command (append '("pline") coords '("c")))
(setq currobj (ssadd (entlast) currobj))
(setq coords (list 
(list 959.4375 537.9416) 
(list 885.415 538.4916) 
(list 885.415 538.3146) 
(list 959.4375 537.8646)))
(apply 'command (append '("pline") coords '("c")))
(setq currobj (ssadd (entlast) currobj))
(setq coords (list 
(list 959.4375 537.7216) 
(list 885.415 538.1716) 
(list 885.415 537.9946) 
(list 959.4375 537.6446)))
(apply 'command (append '("pline") coords '("c")))
(setq currobj (ssadd (entlast) currobj))
(setq coords (list 
(list 959.4375 537.5016) 
(list 885.415 537.8516) 
(list 885.415 537.6746) 
(list 959.4375 537.4246)))
(apply 'command (append '("pline") coords '("c")))
(setq currobj (ssadd (entlast) currobj))
(setq coords (list 
(list 959.4375 537.2816) 
(list 885.415 537.5316) 
(list 885.415 537.3546) 
(list 959.4375 537.2046)))
(apply 'command (append '("pline") coords '("c")))
(setq currobj (ssadd (entlast) currobj))
(setq coords (list 
(list 959.4375 537.0616) 
(list 885.415 537.2116) 
(list 885.415 537.0346) 
(list 959.4375 536.9846)))
(apply 'command (append '("pline") coords '("c")))
(setq currobj (ssadd (entlast) currobj))
(setq coords (list 
(list 959.4375 536.8416) 
(list 885.415 536.8916) 
(list 885.415 536.7146) 
(list 959.4375 536.7646)))
(apply 'command (append '("pline") coords '("c")))
(setq currobj (ssadd (entlast) currobj))
(setq coords (list 
(list 959.4375 536.6216) 
(list 885.415 536.5716) 
(list 885.415 536.3946) 
(list 959.4375 536.5446)))
(apply 'command (append '("pline") coords '("c")))
(setq currobj (ssadd (entlast) currobj))
(setq coords (list 
(list 959.4375 536.4016) 
(list 885.415 536.2516) 
(list 885.415 536.0746) 
(list 959.4375 536.3246)))
(apply 'command (append '("pline") coords '("c")))
(setq currobj (ssadd (entlast) currobj))
(setq coords (list 
(list 959.4375 536.1816) 
(list 885.415 535.9316) 
(list 885.415 535.7546) 
(list 959.4375 536.1046)))
(apply 'command (append '("pline") coords '("c")))
(setq currobj (ssadd (entlast) currobj))
(setq coords (list 
(list 959.4375 535.9616) 
(list 885.415 535.6116) 
(list 885.415 535.4346) 
(list 959.4375 535.8846)))
(apply 'command (append '("pline") coords '("c")))
(setq currobj (ssadd (entlast) currobj))
(setq coords (list 
(list 959.4375 535.7416) 
(list 885.415 535.2916) 
(list 885.415 535.1146) 
(list 959.4375 535.6646)))
(apply 'command (append '("pline") coords '("c")))
(setq currobj (ssadd (entlast) currobj))
(setq coords (list 
(list 959.4375 535.5216) 
(list 885.415 534.9716) 
(list 885.415 534.7946) 
(list 959.4375 535.4446)))
(apply 'command (append '("pline") coords '("c")))
(setq currobj (ssadd (entlast) currobj))
(setq coords (list 
(list 959.4375 535.3016) 
(list 885.415 534.6516) 
(list 885.415 534.4746) 
(list 959.4375 535.2246)))
(apply 'command (append '("pline") coords '("c")))
(setq currobj (ssadd (entlast) currobj))
(command "_layer" "set" "nitride" "")
(command "_layer" "set" "text" "")
(command "_circle" "959.0625,524.0816" "0.075")
(command "_circle" "959.0625,524.3816" "0.075")
(command "_circle" "959.0625,524.6816" "0.075")
(command "_circle" "959.0625,524.9816" "0.075")
(command "_circle" "959.0625,525.2816" "0.075")
(command "_circle" "958.7625,524.0816" "0.075")
(command "_circle" "958.7625,524.3816" "0.075")
(command "_circle" "958.7625,524.6816" "0.075")
(command "_circle" "958.7625,524.9816" "0.075")
(command "_circle" "958.7625,525.2816" "0.075")
(command "_circle" "958.4625,524.0816" "0.075")
(command "_circle" "958.4625,524.3816" "0.075")
(command "_circle" "958.4625,524.6816" "0.075")
(command "_circle" "958.4625,524.9816" "0.075")
(command "_circle" "958.4625,525.2816" "0.075")
(command "_circle" "958.1625,524.0816" "0.075")
(command "_circle" "958.1625,524.3816" "0.075")
(command "_circle" "958.1625,524.6816" "0.075")
(command "_circle" "958.1625,524.9816" "0.075")
(command "_circle" "958.1625,525.2816" "0.075")
(command "_circle" "957.8625,524.0816" "0.075")
(command "_circle" "957.8625,524.3816" "0.075")
(command "_circle" "957.8625,524.6816" "0.075")
(command "_circle" "957.8625,524.9816" "0.075")
(command "_circle" "957.8625,525.2816" "0.075")
(command "_layer" "set" "nitride" "")
(setq coords (list 
(list 960.2625 549.5246) 
(list 960.2625 665.1693) 
(list 959.7375 665.1693) 
(list 959.7375 549.5246)))
(apply 'command (append '("pline") coords '("c")))
(setq currobj (ssadd (entlast) currobj))
(command "_layer" "set" "prebias" "")
(command "_rectangle" "959.7375,549.5246" "960.2625,665.1693")
(setq currobj (ssadd (entlast) currobj))
(command "_layer" "set" "nitride" "")
(setq coords (list 
(list 960.2625 665.1693) 
(list 960.5625 675.1693) 
(list 960.5625 675.1693) 
(list 960.5625 676.1693) 
(list 1034.585 675.4193) 
(list 1034.585 680.3623) 
(list 960.5625 679.6123) 
(list 960.5625 680.6123) 
(list 960.5625 680.6123) 
(list 960.2625 690.6123) 
(list 959.7375 690.6123) 
(list 959.4375 680.6123) 
(list 959.4375 680.6123) 
(list 959.4375 679.6123) 
(list 885.415 680.3623) 
(list 885.415 675.4193) 
(list 959.4375 676.1693) 
(list 959.4375 675.1693) 
(list 959.4375 675.1693) 
(list 959.7375 665.1693)))
(apply 'command (append '("pline") coords '("c")))
(setq currobj (ssadd (entlast) currobj))
(command "_layer" "set" "prebias" "")
(setq coords (list 
(list 959.4375 665.1693) 
(list 959.4375 676.1693) 
(list 885.415 675.4193) 
(list 885.415 680.3623) 
(list 959.4375 679.6123) 
(list 959.4375 690.6123) 
(list 960.5625 690.6123) 
(list 960.5625 679.6123) 
(list 1034.585 680.3623) 
(list 1034.585 675.4193) 
(list 960.5625 676.1693) 
(list 960.5625 665.1693)))
(apply 'command (append '("pline") coords '("c")))
(setq currobj (ssadd (entlast) currobj))
(command "_layer" "set" "nitride" "")
(command "_layer" "set" "fda1" "")
(setq coords (list 
(list 960.5625 676.3123) 
(list 1034.585 675.5623) 
(list 1034.585 675.7393) 
(list 960.5625 676.3893)))
(apply 'command (append '("pline") coords '("c")))
(setq currobj (ssadd (entlast) currobj))
(setq coords (list 
(list 960.5625 676.5323) 
(list 1034.585 675.8823) 
(list 1034.585 676.0593) 
(list 960.5625 676.6093)))
(apply 'command (append '("pline") coords '("c")))
(setq currobj (ssadd (entlast) currobj))
(setq coords (list 
(list 960.5625 676.7523) 
(list 1034.585 676.2023) 
(list 1034.585 676.3793) 
(list 960.5625 676.8293)))
(apply 'command (append '("pline") coords '("c")))
(setq currobj (ssadd (entlast) currobj))
(setq coords (list 
(list 960.5625 676.9723) 
(list 1034.585 676.5223) 
(list 1034.585 676.6993) 
(list 960.5625 677.0493)))
(apply 'command (append '("pline") coords '("c")))
(setq currobj (ssadd (entlast) currobj))
(setq coords (list 
(list 960.5625 677.1923) 
(list 1034.585 676.8423) 
(list 1034.585 677.0193) 
(list 960.5625 677.2693)))
(apply 'command (append '("pline") coords '("c")))
(setq currobj (ssadd (entlast) currobj))
(setq coords (list 
(list 960.5625 677.4123) 
(list 1034.585 677.1623) 
(list 1034.585 677.3393) 
(list 960.5625 677.4893)))
(apply 'command (append '("pline") coords '("c")))
(setq currobj (ssadd (entlast) currobj))
(setq coords (list 
(list 960.5625 677.6323) 
(list 1034.585 677.4823) 
(list 1034.585 677.6593) 
(list 960.5625 677.7093)))
(apply 'command (append '("pline") coords '("c")))
(setq currobj (ssadd (entlast) currobj))
(setq coords (list 
(list 960.5625 677.8523) 
(list 1034.585 677.8023) 
(list 1034.585 677.9793) 
(list 960.5625 677.9293)))
(apply 'command (append '("pline") coords '("c")))
(setq currobj (ssadd (entlast) currobj))
(setq coords (list 
(list 960.5625 678.0723) 
(list 1034.585 678.1223) 
(list 1034.585 678.2993) 
(list 960.5625 678.1493)))
(apply 'command (append '("pline") coords '("c")))
(setq currobj (ssadd (entlast) currobj))
(setq coords (list 
(list 960.5625 678.2923) 
(list 1034.585 678.4423) 
(list 1034.585 678.6193) 
(list 960.5625 678.3693)))
(apply 'command (append '("pline") coords '("c")))
(setq currobj (ssadd (entlast) currobj))
(setq coords (list 
(list 960.5625 678.5123) 
(list 1034.585 678.7623) 
(list 1034.585 678.9393) 
(list 960.5625 678.5893)))
(apply 'command (append '("pline") coords '("c")))
(setq currobj (ssadd (entlast) currobj))
(setq coords (list 
(list 960.5625 678.7323) 
(list 1034.585 679.0823) 
(list 1034.585 679.2593) 
(list 960.5625 678.8093)))
(apply 'command (append '("pline") coords '("c")))
(setq currobj (ssadd (entlast) currobj))
(setq coords (list 
(list 960.5625 678.9523) 
(list 1034.585 679.4023) 
(list 1034.585 679.5793) 
(list 960.5625 679.0293)))
(apply 'command (append '("pline") coords '("c")))
(setq currobj (ssadd (entlast) currobj))
(setq coords (list 
(list 960.5625 679.1723) 
(list 1034.585 679.7223) 
(list 1034.585 679.8993) 
(list 960.5625 679.2493)))
(apply 'command (append '("pline") coords '("c")))
(setq currobj (ssadd (entlast) currobj))
(setq coords (list 
(list 960.5625 679.3923) 
(list 1034.585 680.0423) 
(list 1034.585 680.2193) 
(list 960.5625 679.4693)))
(apply 'command (append '("pline") coords '("c")))
(setq currobj (ssadd (entlast) currobj))
(setq coords (list 
(list 959.4375 679.4693) 
(list 885.415 680.2193) 
(list 885.415 680.0423) 
(list 959.4375 679.3923)))
(apply 'command (append '("pline") coords '("c")))
(setq currobj (ssadd (entlast) currobj))
(setq coords (list 
(list 959.4375 679.2493) 
(list 885.415 679.8993) 
(list 885.415 679.7223) 
(list 959.4375 679.1723)))
(apply 'command (append '("pline") coords '("c")))
(setq currobj (ssadd (entlast) currobj))
(setq coords (list 
(list 959.4375 679.0293) 
(list 885.415 679.5793) 
(list 885.415 679.4023) 
(list 959.4375 678.9523)))
(apply 'command (append '("pline") coords '("c")))
(setq currobj (ssadd (entlast) currobj))
(setq coords (list 
(list 959.4375 678.8093) 
(list 885.415 679.2593) 
(list 885.415 679.0823) 
(list 959.4375 678.7323)))
(apply 'command (append '("pline") coords '("c")))
(setq currobj (ssadd (entlast) currobj))
(setq coords (list 
(list 959.4375 678.5893) 
(list 885.415 678.9393) 
(list 885.415 678.7623) 
(list 959.4375 678.5123)))
(apply 'command (append '("pline") coords '("c")))
(setq currobj (ssadd (entlast) currobj))
(setq coords (list 
(list 959.4375 678.3693) 
(list 885.415 678.6193) 
(list 885.415 678.4423) 
(list 959.4375 678.2923)))
(apply 'command (append '("pline") coords '("c")))
(setq currobj (ssadd (entlast) currobj))
(setq coords (list 
(list 959.4375 678.1493) 
(list 885.415 678.2993) 
(list 885.415 678.1223) 
(list 959.4375 678.0723)))
(apply 'command (append '("pline") coords '("c")))
(setq currobj (ssadd (entlast) currobj))
(setq coords (list 
(list 959.4375 677.9293) 
(list 885.415 677.9793) 
(list 885.415 677.8023) 
(list 959.4375 677.8523)))
(apply 'command (append '("pline") coords '("c")))
(setq currobj (ssadd (entlast) currobj))
(setq coords (list 
(list 959.4375 677.7093) 
(list 885.415 677.6593) 
(list 885.415 677.4823) 
(list 959.4375 677.6323)))
(apply 'command (append '("pline") coords '("c")))
(setq currobj (ssadd (entlast) currobj))
(setq coords (list 
(list 959.4375 677.4893) 
(list 885.415 677.3393) 
(list 885.415 677.1623) 
(list 959.4375 677.4123)))
(apply 'command (append '("pline") coords '("c")))
(setq currobj (ssadd (entlast) currobj))
(setq coords (list 
(list 959.4375 677.2693) 
(list 885.415 677.0193) 
(list 885.415 676.8423) 
(list 959.4375 677.1923)))
(apply 'command (append '("pline") coords '("c")))
(setq currobj (ssadd (entlast) currobj))
(setq coords (list 
(list 959.4375 677.0493) 
(list 885.415 676.6993) 
(list 885.415 676.5223) 
(list 959.4375 676.9723)))
(apply 'command (append '("pline") coords '("c")))
(setq currobj (ssadd (entlast) currobj))
(setq coords (list 
(list 959.4375 676.8293) 
(list 885.415 676.3793) 
(list 885.415 676.2023) 
(list 959.4375 676.7523)))
(apply 'command (append '("pline") coords '("c")))
(setq currobj (ssadd (entlast) currobj))
(setq coords (list 
(list 959.4375 676.6093) 
(list 885.415 676.0593) 
(list 885.415 675.8823) 
(list 959.4375 676.5323)))
(apply 'command (append '("pline") coords '("c")))
(setq currobj (ssadd (entlast) currobj))
(setq coords (list 
(list 959.4375 676.3893) 
(list 885.415 675.7393) 
(list 885.415 675.5623) 
(list 959.4375 676.3123)))
(apply 'command (append '("pline") coords '("c")))
(setq currobj (ssadd (entlast) currobj))
(command "_layer" "set" "nitride" "")
(command "_layer" "set" "text" "")
(command "_circle" "959.0625,665.1693" "0.075")
(command "_circle" "959.0625,665.4693" "0.075")
(command "_circle" "959.0625,665.7693" "0.075")
(command "_circle" "959.0625,666.0693" "0.075")
(command "_circle" "959.0625,666.3693" "0.075")
(command "_circle" "958.7625,665.1693" "0.075")
(command "_circle" "958.7625,665.4693" "0.075")
(command "_circle" "958.7625,665.7693" "0.075")
(command "_circle" "958.7625,666.0693" "0.075")
(command "_circle" "958.7625,666.3693" "0.075")
(command "_circle" "958.4625,665.1693" "0.075")
(command "_circle" "958.4625,665.4693" "0.075")
(command "_circle" "958.4625,665.7693" "0.075")
(command "_circle" "958.4625,666.0693" "0.075")
(command "_circle" "958.4625,666.3693" "0.075")
(command "_circle" "958.1625,665.1693" "0.075")
(command "_circle" "958.1625,665.4693" "0.075")
(command "_circle" "958.1625,665.7693" "0.075")
(command "_circle" "958.1625,666.0693" "0.075")
(command "_circle" "958.1625,666.3693" "0.075")
(command "_circle" "957.8625,665.1693" "0.075")
(command "_circle" "957.8625,665.4693" "0.075")
(command "_circle" "957.8625,665.7693" "0.075")
(command "_circle" "957.8625,666.0693" "0.075")
(command "_circle" "957.8625,666.3693" "0.075")
(command "_layer" "set" "nitride" "")
(setq coords (list 
(list 960.2625 690.6123) 
(list 960.2625 806.257) 
(list 959.7375 806.257) 
(list 959.7375 690.6123)))
(apply 'command (append '("pline") coords '("c")))
(setq currobj (ssadd (entlast) currobj))
(command "_layer" "set" "prebias" "")
(command "_rectangle" "959.7375,690.6123" "960.2625,806.257")
(setq currobj (ssadd (entlast) currobj))
(command "_layer" "set" "nitride" "")
(setq coords (list 
(list 960.2625 806.257) 
(list 960.5625 816.257) 
(list 960.5625 816.257) 
(list 960.5625 817.257) 
(list 1034.585 816.507) 
(list 1034.585 821.45) 
(list 960.5625 820.7) 
(list 960.5625 821.7) 
(list 960.5625 821.7) 
(list 960.2625 831.7) 
(list 959.7375 831.7) 
(list 959.4375 821.7) 
(list 959.4375 821.7) 
(list 959.4375 820.7) 
(list 885.415 821.45) 
(list 885.415 816.507) 
(list 959.4375 817.257) 
(list 959.4375 816.257) 
(list 959.4375 816.257) 
(list 959.7375 806.257)))
(apply 'command (append '("pline") coords '("c")))
(setq currobj (ssadd (entlast) currobj))
(command "_layer" "set" "prebias" "")
(setq coords (list 
(list 959.4375 806.257) 
(list 959.4375 817.257) 
(list 885.415 816.507) 
(list 885.415 821.45) 
(list 959.4375 820.7) 
(list 959.4375 831.7) 
(list 960.5625 831.7) 
(list 960.5625 820.7) 
(list 1034.585 821.45) 
(list 1034.585 816.507) 
(list 960.5625 817.257) 
(list 960.5625 806.257)))
(apply 'command (append '("pline") coords '("c")))
(setq currobj (ssadd (entlast) currobj))
(command "_layer" "set" "nitride" "")
(command "_layer" "set" "fda1" "")
(setq coords (list 
(list 960.5625 817.4) 
(list 1034.585 816.65) 
(list 1034.585 816.827) 
(list 960.5625 817.477)))
(apply 'command (append '("pline") coords '("c")))
(setq currobj (ssadd (entlast) currobj))
(setq coords (list 
(list 960.5625 817.62) 
(list 1034.585 816.97) 
(list 1034.585 817.147) 
(list 960.5625 817.697)))
(apply 'command (append '("pline") coords '("c")))
(setq currobj (ssadd (entlast) currobj))
(setq coords (list 
(list 960.5625 817.84) 
(list 1034.585 817.29) 
(list 1034.585 817.467) 
(list 960.5625 817.917)))
(apply 'command (append '("pline") coords '("c")))
(setq currobj (ssadd (entlast) currobj))
(setq coords (list 
(list 960.5625 818.06) 
(list 1034.585 817.61) 
(list 1034.585 817.787) 
(list 960.5625 818.137)))
(apply 'command (append '("pline") coords '("c")))
(setq currobj (ssadd (entlast) currobj))
(setq coords (list 
(list 960.5625 818.28) 
(list 1034.585 817.93) 
(list 1034.585 818.107) 
(list 960.5625 818.357)))
(apply 'command (append '("pline") coords '("c")))
(setq currobj (ssadd (entlast) currobj))
(setq coords (list 
(list 960.5625 818.5) 
(list 1034.585 818.25) 
(list 1034.585 818.427) 
(list 960.5625 818.577)))
(apply 'command (append '("pline") coords '("c")))
(setq currobj (ssadd (entlast) currobj))
(setq coords (list 
(list 960.5625 818.72) 
(list 1034.585 818.57) 
(list 1034.585 818.747) 
(list 960.5625 818.797)))
(apply 'command (append '("pline") coords '("c")))
(setq currobj (ssadd (entlast) currobj))
(setq coords (list 
(list 960.5625 818.94) 
(list 1034.585 818.89) 
(list 1034.585 819.067) 
(list 960.5625 819.017)))
(apply 'command (append '("pline") coords '("c")))
(setq currobj (ssadd (entlast) currobj))
(setq coords (list 
(list 960.5625 819.16) 
(list 1034.585 819.21) 
(list 1034.585 819.387) 
(list 960.5625 819.237)))
(apply 'command (append '("pline") coords '("c")))
(setq currobj (ssadd (entlast) currobj))
(setq coords (list 
(list 960.5625 819.38) 
(list 1034.585 819.53) 
(list 1034.585 819.707) 
(list 960.5625 819.457)))
(apply 'command (append '("pline") coords '("c")))
(setq currobj (ssadd (entlast) currobj))
(setq coords (list 
(list 960.5625 819.6) 
(list 1034.585 819.85) 
(list 1034.585 820.027) 
(list 960.5625 819.677)))
(apply 'command (append '("pline") coords '("c")))
(setq currobj (ssadd (entlast) currobj))
(setq coords (list 
(list 960.5625 819.82) 
(list 1034.585 820.17) 
(list 1034.585 820.347) 
(list 960.5625 819.897)))
(apply 'command (append '("pline") coords '("c")))
(setq currobj (ssadd (entlast) currobj))
(setq coords (list 
(list 960.5625 820.04) 
(list 1034.585 820.49) 
(list 1034.585 820.667) 
(list 960.5625 820.117)))
(apply 'command (append '("pline") coords '("c")))
(setq currobj (ssadd (entlast) currobj))
(setq coords (list 
(list 960.5625 820.26) 
(list 1034.585 820.81) 
(list 1034.585 820.987) 
(list 960.5625 820.337)))
(apply 'command (append '("pline") coords '("c")))
(setq currobj (ssadd (entlast) currobj))
(setq coords (list 
(list 960.5625 820.48) 
(list 1034.585 821.13) 
(list 1034.585 821.307) 
(list 960.5625 820.557)))
(apply 'command (append '("pline") coords '("c")))
(setq currobj (ssadd (entlast) currobj))
(setq coords (list 
(list 959.4375 820.557) 
(list 885.415 821.307) 
(list 885.415 821.13) 
(list 959.4375 820.48)))
(apply 'command (append '("pline") coords '("c")))
(setq currobj (ssadd (entlast) currobj))
(setq coords (list 
(list 959.4375 820.337) 
(list 885.415 820.987) 
(list 885.415 820.81) 
(list 959.4375 820.26)))
(apply 'command (append '("pline") coords '("c")))
(setq currobj (ssadd (entlast) currobj))
(setq coords (list 
(list 959.4375 820.117) 
(list 885.415 820.667) 
(list 885.415 820.49) 
(list 959.4375 820.04)))
(apply 'command (append '("pline") coords '("c")))
(setq currobj (ssadd (entlast) currobj))
(setq coords (list 
(list 959.4375 819.897) 
(list 885.415 820.347) 
(list 885.415 820.17) 
(list 959.4375 819.82)))
(apply 'command (append '("pline") coords '("c")))
(setq currobj (ssadd (entlast) currobj))
(setq coords (list 
(list 959.4375 819.677) 
(list 885.415 820.027) 
(list 885.415 819.85) 
(list 959.4375 819.6)))
(apply 'command (append '("pline") coords '("c")))
(setq currobj (ssadd (entlast) currobj))
(setq coords (list 
(list 959.4375 819.457) 
(list 885.415 819.707) 
(list 885.415 819.53) 
(list 959.4375 819.38)))
(apply 'command (append '("pline") coords '("c")))
(setq currobj (ssadd (entlast) currobj))
(setq coords (list 
(list 959.4375 819.237) 
(list 885.415 819.387) 
(list 885.415 819.21) 
(list 959.4375 819.16)))
(apply 'command (append '("pline") coords '("c")))
(setq currobj (ssadd (entlast) currobj))
(setq coords (list 
(list 959.4375 819.017) 
(list 885.415 819.067) 
(list 885.415 818.89) 
(list 959.4375 818.94)))
(apply 'command (append '("pline") coords '("c")))
(setq currobj (ssadd (entlast) currobj))
(setq coords (list 
(list 959.4375 818.797) 
(list 885.415 818.747) 
(list 885.415 818.57) 
(list 959.4375 818.72)))
(apply 'command (append '("pline") coords '("c")))
(setq currobj (ssadd (entlast) currobj))
(setq coords (list 
(list 959.4375 818.577) 
(list 885.415 818.427) 
(list 885.415 818.25) 
(list 959.4375 818.5)))
(apply 'command (append '("pline") coords '("c")))
(setq currobj (ssadd (entlast) currobj))
(setq coords (list 
(list 959.4375 818.357) 
(list 885.415 818.107) 
(list 885.415 817.93) 
(list 959.4375 818.28)))
(apply 'command (append '("pline") coords '("c")))
(setq currobj (ssadd (entlast) currobj))
(setq coords (list 
(list 959.4375 818.137) 
(list 885.415 817.787) 
(list 885.415 817.61) 
(list 959.4375 818.06)))
(apply 'command (append '("pline") coords '("c")))
(setq currobj (ssadd (entlast) currobj))
(setq coords (list 
(list 959.4375 817.917) 
(list 885.415 817.467) 
(list 885.415 817.29) 
(list 959.4375 817.84)))
(apply 'command (append '("pline") coords '("c")))
(setq currobj (ssadd (entlast) currobj))
(setq coords (list 
(list 959.4375 817.697) 
(list 885.415 817.147) 
(list 885.415 816.97) 
(list 959.4375 817.62)))
(apply 'command (append '("pline") coords '("c")))
(setq currobj (ssadd (entlast) currobj))
(setq coords (list 
(list 959.4375 817.477) 
(list 885.415 816.827) 
(list 885.415 816.65) 
(list 959.4375 817.4)))
(apply 'command (append '("pline") coords '("c")))
(setq currobj (ssadd (entlast) currobj))
(command "_layer" "set" "nitride" "")
(command "_layer" "set" "text" "")
(command "_circle" "959.0625,806.257" "0.075")
(command "_circle" "959.0625,806.557" "0.075")
(command "_circle" "959.0625,806.857" "0.075")
(command "_circle" "959.0625,807.157" "0.075")
(command "_circle" "959.0625,807.457" "0.075")
(command "_circle" "958.7625,806.257" "0.075")
(command "_circle" "958.7625,806.557" "0.075")
(command "_circle" "958.7625,806.857" "0.075")
(command "_circle" "958.7625,807.157" "0.075")
(command "_circle" "958.7625,807.457" "0.075")
(command "_circle" "958.4625,806.257" "0.075")
(command "_circle" "958.4625,806.557" "0.075")
(command "_circle" "958.4625,806.857" "0.075")
(command "_circle" "958.4625,807.157" "0.075")
(command "_circle" "958.4625,807.457" "0.075")
(command "_circle" "958.1625,806.257" "0.075")
(command "_circle" "958.1625,806.557" "0.075")
(command "_circle" "958.1625,806.857" "0.075")
(command "_circle" "958.1625,807.157" "0.075")
(command "_circle" "958.1625,807.457" "0.075")
(command "_circle" "957.8625,806.257" "0.075")
(command "_circle" "957.8625,806.557" "0.075")
(command "_circle" "957.8625,806.857" "0.075")
(command "_circle" "957.8625,807.157" "0.075")
(command "_circle" "957.8625,807.457" "0.075")
(command "_layer" "set" "nitride" "")
(setq coords (list 
(list 960.2625 831.7) 
(list 960.2625 836.7) 
(list 959.7375 836.7) 
(list 959.7375 831.7)))
(apply 'command (append '("pline") coords '("c")))
(setq currobj (ssadd (entlast) currobj))
(command "_layer" "set" "prebias" "")
(command "_rectangle" "959.7375,831.7" "960.2625,836.7")
(setq currobj (ssadd (entlast) currobj))
(command "_layer" "set" "nitride" "")
(setq cooledsinglenanobeam3 currobj)
(setq currobj nil)
(setq currobj (ssadd))
; DRAWING PHOTONIC CRYSTAL
(command "_layer" "set" "negYjunc" "")
(setq coords (list 
(list 960.135 866.7) 
(list 960 851.7) 
(list 960 866.7)))
(apply 'command (append '("pline") coords '("c")))
(setq currobj (ssadd (entlast) currobj))
(setq coords (list 
(list 960.2625 836.7) 
(list 960.415 866.7) 
(list 961.124 866.7) 
(list 961.124 836.7)))
(apply 'command (append '("pline") coords '("c")))
(setq currobj (ssadd (entlast) currobj))
(setq coords (list 
(list 959.865 866.7) 
(list 960 851.7) 
(list 960 866.7)))
(apply 'command (append '("pline") coords '("c")))
(setq currobj (ssadd (entlast) currobj))
(setq coords (list 
(list 959.7375 836.7) 
(list 959.585 866.7) 
(list 958.876 866.7) 
(list 958.876 836.7)))
(apply 'command (append '("pline") coords '("c")))
(setq currobj (ssadd (entlast) currobj))
(command "_layer" "set" "nitride" "")
(setq yjunction3 currobj)
(setq currobj nil)
(setq currobj (ssadd))
(setq tap3 nil)
(setq tap3 (ssadd))
(command "_layer" "set" "phc" "")
(setq coords (list 
(list 960 866.7) 
(list 960.135 866.7) 
(list 960.135 866.7103) 
(list 960.135 866.7206) 
(list 960.135 866.7308) 
(list 960.135 866.7411) 
(list 960.135 866.7514) 
(list 960.135 866.7617) 
(list 960.135 866.7719) 
(list 960.135 866.7822) 
(list 960.135 866.7925) 
(list 960.135 866.8028) 
(list 960.135 866.8131) 
(list 960.135 866.8233) 
(list 960.135 866.8336) 
(list 960.135 866.8439) 
(list 960.135 866.8542) 
(list 960.135 866.8644) 
(list 960.135 866.8747) 
(list 960.135 866.885) 
(list 960.135 866.8953) 
(list 960.135 866.9056) 
(list 960.135 866.9158) 
(list 960.135 866.9261) 
(list 960.135 866.9364) 
(list 960.135 866.9467) 
(list 960.135 866.9569) 
(list 960.135 866.9672) 
(list 960.135 866.9775) 
(list 960.135 866.9878) 
(list 960.135 866.9981) 
(list 960.135 867.0083) 
(list 960.135 867.0186) 
(list 960.135 867.0289) 
(list 960.135 867.0392) 
(list 960.135 867.0494) 
(list 960.135 867.0597) 
(list 960.135 867.07) 
(list 960 867.07)))
(apply 'command (append '("pline") coords '("c")))
(setq tap3 (ssadd (entlast) tap3))
(command "_mirror" (entlast) "" "960,900" "960,901" "No")
(setq tap3 (ssadd (entlast) tap3))
(setq coords (list 
(list 960.4248 866.7) 
(list 960.415 866.7) 
(list 960.4153 866.7103) 
(list 960.4155 866.7206) 
(list 960.4157 866.7308) 
(list 960.4159 866.7411) 
(list 960.4159 866.7514) 
(list 960.4159 866.7617) 
(list 960.4158 866.7719) 
(list 960.4155 866.7822) 
(list 960.4152 866.7925) 
(list 960.4148 866.8028) 
(list 960.4143 866.8131) 
(list 960.4138 866.8233) 
(list 960.4132 866.8336) 
(list 960.4126 866.8439) 
(list 960.4121 866.8542) 
(list 960.4116 866.8644) 
(list 960.4112 866.8747) 
(list 960.4109 866.885) 
(list 960.4107 866.8953) 
(list 960.4107 866.9056) 
(list 960.4109 866.9158) 
(list 960.4113 866.9261) 
(list 960.4118 866.9364) 
(list 960.4125 866.9467) 
(list 960.4134 866.9569) 
(list 960.4144 866.9672) 
(list 960.4156 866.9775) 
(list 960.4168 866.9878) 
(list 960.4181 866.9981) 
(list 960.4194 867.0083) 
(list 960.4207 867.0186) 
(list 960.4218 867.0289) 
(list 960.4229 867.0392) 
(list 960.4237 867.0494) 
(list 960.4244 867.0597) 
(list 960.4248 867.07) 
(list 960.4248 867.07)))
(apply 'command (append '("pline") coords '("c")))
(setq tap3 (ssadd (entlast) tap3))
(command "_mirror" (entlast) "" "960,900" "960,901" "No")
(setq tap3 (ssadd (entlast) tap3))
(setq coords (list 
(list 961.124 866.7) 
(list 960.4248 866.7) 
(list 960.4248 866.7103) 
(list 960.4248 866.7206) 
(list 960.4248 866.7308) 
(list 960.4248 866.7411) 
(list 960.4248 866.7514) 
(list 960.4248 866.7617) 
(list 960.4248 866.7719) 
(list 960.4248 866.7822) 
(list 960.4248 866.7925) 
(list 960.4248 866.8028) 
(list 960.4248 866.8131) 
(list 960.4248 866.8233) 
(list 960.4248 866.8336) 
(list 960.4248 866.8439) 
(list 960.4248 866.8542) 
(list 960.4248 866.8644) 
(list 960.4248 866.8747) 
(list 960.4248 866.885) 
(list 960.4248 866.8953) 
(list 960.4248 866.9056) 
(list 960.4248 866.9158) 
(list 960.4248 866.9261) 
(list 960.4248 866.9364) 
(list 960.4248 866.9467) 
(list 960.4248 866.9569) 
(list 960.4248 866.9672) 
(list 960.4248 866.9775) 
(list 960.4248 866.9878) 
(list 960.4248 866.9981) 
(list 960.4248 867.0083) 
(list 960.4248 867.0186) 
(list 960.4248 867.0289) 
(list 960.4248 867.0392) 
(list 960.4248 867.0494) 
(list 960.4248 867.0597) 
(list 960.4248 867.07) 
(list 961.124 867.07)))
(apply 'command (append '("pline") coords '("c")))
(setq tap3 (ssadd (entlast) tap3))
(command "_mirror" (entlast) "" "960,900" "960,901" "No")
(setq tap3 (ssadd (entlast) tap3))
(setq coords (list 
(list 960 867.07) 
(list 960.135 867.07) 
(list 960.135 867.0803) 
(list 960.135 867.0906) 
(list 960.135 867.1008) 
(list 960.135 867.1111) 
(list 960.135 867.1214) 
(list 960.135 867.1317) 
(list 960.135 867.1419) 
(list 960.135 867.1522) 
(list 960.135 867.1625) 
(list 960.135 867.1728) 
(list 960.135 867.1831) 
(list 960.135 867.1933) 
(list 960.135 867.2036) 
(list 960.135 867.2139) 
(list 960.135 867.2242) 
(list 960.135 867.2344) 
(list 960.135 867.2447) 
(list 960.135 867.255) 
(list 960.135 867.2653) 
(list 960.135 867.2756) 
(list 960.135 867.2858) 
(list 960.135 867.2961) 
(list 960.135 867.3064) 
(list 960.135 867.3167) 
(list 960.135 867.3269) 
(list 960.135 867.3372) 
(list 960.135 867.3475) 
(list 960.135 867.3578) 
(list 960.135 867.3681) 
(list 960.135 867.3783) 
(list 960.135 867.3886) 
(list 960.135 867.3989) 
(list 960.135 867.4092) 
(list 960.135 867.4194) 
(list 960.135 867.4297) 
(list 960.135 867.44) 
(list 960 867.44)))
(apply 'command (append '("pline") coords '("c")))
(setq tap3 (ssadd (entlast) tap3))
(command "_mirror" (entlast) "" "960,900" "960,901" "No")
(setq tap3 (ssadd (entlast) tap3))
(setq coords (list 
(list 960.4346 867.07) 
(list 960.4248 867.07) 
(list 960.4249 867.0803) 
(list 960.4248 867.0906) 
(list 960.4243 867.1008) 
(list 960.4235 867.1111) 
(list 960.4225 867.1214) 
(list 960.4212 867.1317) 
(list 960.4196 867.1419) 
(list 960.4179 867.1522) 
(list 960.416 867.1625) 
(list 960.414 867.1728) 
(list 960.412 867.1831) 
(list 960.4101 867.1933) 
(list 960.4082 867.2036) 
(list 960.4065 867.2139) 
(list 960.4051 867.2242) 
(list 960.4039 867.2344) 
(list 960.4031 867.2447) 
(list 960.4027 867.255) 
(list 960.4027 867.2653) 
(list 960.4031 867.2756) 
(list 960.4039 867.2858) 
(list 960.4052 867.2961) 
(list 960.4068 867.3064) 
(list 960.4088 867.3167) 
(list 960.4111 867.3269) 
(list 960.4137 867.3372) 
(list 960.4164 867.3475) 
(list 960.4192 867.3578) 
(list 960.422 867.3681) 
(list 960.4247 867.3783) 
(list 960.4273 867.3886) 
(list 960.4295 867.3989) 
(list 960.4315 867.4092) 
(list 960.433 867.4194) 
(list 960.4341 867.4297) 
(list 960.4346 867.44) 
(list 960.4346 867.44)))
(apply 'command (append '("pline") coords '("c")))
(setq tap3 (ssadd (entlast) tap3))
(command "_mirror" (entlast) "" "960,900" "960,901" "No")
(setq tap3 (ssadd (entlast) tap3))
(setq coords (list 
(list 961.124 867.07) 
(list 960.4346 867.07) 
(list 960.4346 867.0803) 
(list 960.4346 867.0906) 
(list 960.4346 867.1008) 
(list 960.4346 867.1111) 
(list 960.4346 867.1214) 
(list 960.4346 867.1317) 
(list 960.4346 867.1419) 
(list 960.4346 867.1522) 
(list 960.4346 867.1625) 
(list 960.4346 867.1728) 
(list 960.4346 867.1831) 
(list 960.4346 867.1933) 
(list 960.4346 867.2036) 
(list 960.4346 867.2139) 
(list 960.4346 867.2242) 
(list 960.4346 867.2344) 
(list 960.4346 867.2447) 
(list 960.4346 867.255) 
(list 960.4346 867.2653) 
(list 960.4346 867.2756) 
(list 960.4346 867.2858) 
(list 960.4346 867.2961) 
(list 960.4346 867.3064) 
(list 960.4346 867.3167) 
(list 960.4346 867.3269) 
(list 960.4346 867.3372) 
(list 960.4346 867.3475) 
(list 960.4346 867.3578) 
(list 960.4346 867.3681) 
(list 960.4346 867.3783) 
(list 960.4346 867.3886) 
(list 960.4346 867.3989) 
(list 960.4346 867.4092) 
(list 960.4346 867.4194) 
(list 960.4346 867.4297) 
(list 960.4346 867.44) 
(list 961.124 867.44)))
(apply 'command (append '("pline") coords '("c")))
(setq tap3 (ssadd (entlast) tap3))
(command "_mirror" (entlast) "" "960,900" "960,901" "No")
(setq tap3 (ssadd (entlast) tap3))
(setq coords (list 
(list 960 867.44) 
(list 960.135 867.44) 
(list 960.135 867.4503) 
(list 960.135 867.4606) 
(list 960.135 867.4708) 
(list 960.135 867.4811) 
(list 960.135 867.4914) 
(list 960.135 867.5017) 
(list 960.135 867.5119) 
(list 960.135 867.5222) 
(list 960.135 867.5325) 
(list 960.135 867.5428) 
(list 960.135 867.5531) 
(list 960.135 867.5633) 
(list 960.135 867.5736) 
(list 960.135 867.5839) 
(list 960.135 867.5942) 
(list 960.135 867.6044) 
(list 960.135 867.6147) 
(list 960.135 867.625) 
(list 960.135 867.6353) 
(list 960.135 867.6456) 
(list 960.135 867.6558) 
(list 960.135 867.6661) 
(list 960.135 867.6764) 
(list 960.135 867.6867) 
(list 960.135 867.6969) 
(list 960.135 867.7072) 
(list 960.135 867.7175) 
(list 960.135 867.7278) 
(list 960.135 867.7381) 
(list 960.135 867.7483) 
(list 960.135 867.7586) 
(list 960.135 867.7689) 
(list 960.135 867.7792) 
(list 960.135 867.7894) 
(list 960.135 867.7997) 
(list 960.135 867.81) 
(list 960 867.81)))
(apply 'command (append '("pline") coords '("c")))
(setq tap3 (ssadd (entlast) tap3))
(command "_mirror" (entlast) "" "960,900" "960,901" "No")
(setq tap3 (ssadd (entlast) tap3))
(setq coords (list 
(list 960.4444 867.44) 
(list 960.4346 867.44) 
(list 960.4346 867.4503) 
(list 960.434 867.4606) 
(list 960.4329 867.4708) 
(list 960.4312 867.4811) 
(list 960.4291 867.4914) 
(list 960.4265 867.5017) 
(list 960.4235 867.5119) 
(list 960.4203 867.5222) 
(list 960.4168 867.5325) 
(list 960.4133 867.5428) 
(list 960.4097 867.5531) 
(list 960.4064 867.5633) 
(list 960.4032 867.5736) 
(list 960.4004 867.5839) 
(list 960.3981 867.5942) 
(list 960.3963 867.6044) 
(list 960.3951 867.6147) 
(list 960.3945 867.625) 
(list 960.3946 867.6353) 
(list 960.3954 867.6456) 
(list 960.3969 867.6558) 
(list 960.3991 867.6661) 
(list 960.4018 867.6764) 
(list 960.4051 867.6867) 
(list 960.4089 867.6969) 
(list 960.4129 867.7072) 
(list 960.4172 867.7175) 
(list 960.4216 867.7278) 
(list 960.4259 867.7381) 
(list 960.43 867.7483) 
(list 960.4338 867.7586) 
(list 960.4372 867.7689) 
(list 960.4401 867.7792) 
(list 960.4423 867.7894) 
(list 960.4437 867.7997) 
(list 960.4444 867.81) 
(list 960.4444 867.81)))
(apply 'command (append '("pline") coords '("c")))
(setq tap3 (ssadd (entlast) tap3))
(command "_mirror" (entlast) "" "960,900" "960,901" "No")
(setq tap3 (ssadd (entlast) tap3))
(setq coords (list 
(list 961.124 867.44) 
(list 960.4444 867.44) 
(list 960.4444 867.4503) 
(list 960.4444 867.4606) 
(list 960.4444 867.4708) 
(list 960.4444 867.4811) 
(list 960.4444 867.4914) 
(list 960.4444 867.5017) 
(list 960.4444 867.5119) 
(list 960.4444 867.5222) 
(list 960.4444 867.5325) 
(list 960.4444 867.5428) 
(list 960.4444 867.5531) 
(list 960.4444 867.5633) 
(list 960.4444 867.5736) 
(list 960.4444 867.5839) 
(list 960.4444 867.5942) 
(list 960.4444 867.6044) 
(list 960.4444 867.6147) 
(list 960.4444 867.625) 
(list 960.4444 867.6353) 
(list 960.4444 867.6456) 
(list 960.4444 867.6558) 
(list 960.4444 867.6661) 
(list 960.4444 867.6764) 
(list 960.4444 867.6867) 
(list 960.4444 867.6969) 
(list 960.4444 867.7072) 
(list 960.4444 867.7175) 
(list 960.4444 867.7278) 
(list 960.4444 867.7381) 
(list 960.4444 867.7483) 
(list 960.4444 867.7586) 
(list 960.4444 867.7689) 
(list 960.4444 867.7792) 
(list 960.4444 867.7894) 
(list 960.4444 867.7997) 
(list 960.4444 867.81) 
(list 961.124 867.81)))
(apply 'command (append '("pline") coords '("c")))
(setq tap3 (ssadd (entlast) tap3))
(command "_mirror" (entlast) "" "960,900" "960,901" "No")
(setq tap3 (ssadd (entlast) tap3))
(setq coords (list 
(list 960 867.81) 
(list 960.135 867.81) 
(list 960.135 867.8203) 
(list 960.135 867.8306) 
(list 960.135 867.8408) 
(list 960.135 867.8511) 
(list 960.135 867.8614) 
(list 960.135 867.8717) 
(list 960.135 867.8819) 
(list 960.135 867.8922) 
(list 960.135 867.9025) 
(list 960.135 867.9128) 
(list 960.135 867.9231) 
(list 960.135 867.9333) 
(list 960.135 867.9436) 
(list 960.135 867.9539) 
(list 960.135 867.9642) 
(list 960.135 867.9744) 
(list 960.135 867.9847) 
(list 960.135 867.995) 
(list 960.135 868.0053) 
(list 960.135 868.0156) 
(list 960.135 868.0258) 
(list 960.135 868.0361) 
(list 960.135 868.0464) 
(list 960.135 868.0567) 
(list 960.135 868.0669) 
(list 960.135 868.0772) 
(list 960.135 868.0875) 
(list 960.135 868.0978) 
(list 960.135 868.1081) 
(list 960.135 868.1183) 
(list 960.135 868.1286) 
(list 960.135 868.1389) 
(list 960.135 868.1492) 
(list 960.135 868.1594) 
(list 960.135 868.1697) 
(list 960.135 868.18) 
(list 960 868.18)))
(apply 'command (append '("pline") coords '("c")))
(setq tap3 (ssadd (entlast) tap3))
(command "_mirror" (entlast) "" "960,900" "960,901" "No")
(setq tap3 (ssadd (entlast) tap3))
(setq coords (list 
(list 960.4542 867.81) 
(list 960.4444 867.81) 
(list 960.4443 867.8203) 
(list 960.4433 867.8306) 
(list 960.4415 867.8408) 
(list 960.4389 867.8511) 
(list 960.4357 867.8614) 
(list 960.4318 867.8717) 
(list 960.4274 867.8819) 
(list 960.4226 867.8922) 
(list 960.4176 867.9025) 
(list 960.4125 867.9128) 
(list 960.4075 867.9231) 
(list 960.4027 867.9333) 
(list 960.3982 867.9436) 
(list 960.3943 867.9539) 
(list 960.3911 867.9642) 
(list 960.3886 867.9744) 
(list 960.387 867.9847) 
(list 960.3863 867.995) 
(list 960.3866 868.0053) 
(list 960.3878 868.0156) 
(list 960.3899 868.0258) 
(list 960.393 868.0361) 
(list 960.3969 868.0464) 
(list 960.4014 868.0567) 
(list 960.4066 868.0669) 
(list 960.4122 868.0772) 
(list 960.418 868.0875) 
(list 960.4239 868.0978) 
(list 960.4298 868.1081) 
(list 960.4353 868.1183) 
(list 960.4404 868.1286) 
(list 960.4449 868.1389) 
(list 960.4487 868.1492) 
(list 960.4515 868.1594) 
(list 960.4534 868.1697) 
(list 960.4542 868.18) 
(list 960.4542 868.18)))
(apply 'command (append '("pline") coords '("c")))
(setq tap3 (ssadd (entlast) tap3))
(command "_mirror" (entlast) "" "960,900" "960,901" "No")
(setq tap3 (ssadd (entlast) tap3))
(setq coords (list 
(list 961.124 867.81) 
(list 960.4542 867.81) 
(list 960.4542 867.8203) 
(list 960.4542 867.8306) 
(list 960.4542 867.8408) 
(list 960.4542 867.8511) 
(list 960.4542 867.8614) 
(list 960.4542 867.8717) 
(list 960.4542 867.8819) 
(list 960.4542 867.8922) 
(list 960.4542 867.9025) 
(list 960.4542 867.9128) 
(list 960.4542 867.9231) 
(list 960.4542 867.9333) 
(list 960.4542 867.9436) 
(list 960.4542 867.9539) 
(list 960.4542 867.9642) 
(list 960.4542 867.9744) 
(list 960.4542 867.9847) 
(list 960.4542 867.995) 
(list 960.4542 868.0053) 
(list 960.4542 868.0156) 
(list 960.4542 868.0258) 
(list 960.4542 868.0361) 
(list 960.4542 868.0464) 
(list 960.4542 868.0567) 
(list 960.4542 868.0669) 
(list 960.4542 868.0772) 
(list 960.4542 868.0875) 
(list 960.4542 868.0978) 
(list 960.4542 868.1081) 
(list 960.4542 868.1183) 
(list 960.4542 868.1286) 
(list 960.4542 868.1389) 
(list 960.4542 868.1492) 
(list 960.4542 868.1594) 
(list 960.4542 868.1697) 
(list 960.4542 868.18) 
(list 961.124 868.18)))
(apply 'command (append '("pline") coords '("c")))
(setq tap3 (ssadd (entlast) tap3))
(command "_mirror" (entlast) "" "960,900" "960,901" "No")
(setq tap3 (ssadd (entlast) tap3))
(setq coords (list 
(list 960 868.18) 
(list 960.135 868.18) 
(list 960.135 868.1903) 
(list 960.135 868.2006) 
(list 960.135 868.2108) 
(list 960.135 868.2211) 
(list 960.135 868.2314) 
(list 960.135 868.2417) 
(list 960.135 868.2519) 
(list 960.135 868.2622) 
(list 960.135 868.2725) 
(list 960.135 868.2828) 
(list 960.135 868.2931) 
(list 960.135 868.3033) 
(list 960.135 868.3136) 
(list 960.135 868.3239) 
(list 960.135 868.3342) 
(list 960.135 868.3444) 
(list 960.135 868.3547) 
(list 960.135 868.365) 
(list 960.135 868.3753) 
(list 960.135 868.3856) 
(list 960.135 868.3958) 
(list 960.135 868.4061) 
(list 960.135 868.4164) 
(list 960.135 868.4267) 
(list 960.135 868.4369) 
(list 960.135 868.4472) 
(list 960.135 868.4575) 
(list 960.135 868.4678) 
(list 960.135 868.4781) 
(list 960.135 868.4883) 
(list 960.135 868.4986) 
(list 960.135 868.5089) 
(list 960.135 868.5192) 
(list 960.135 868.5294) 
(list 960.135 868.5397) 
(list 960.135 868.55) 
(list 960 868.55)))
(apply 'command (append '("pline") coords '("c")))
(setq tap3 (ssadd (entlast) tap3))
(command "_mirror" (entlast) "" "960,900" "960,901" "No")
(setq tap3 (ssadd (entlast) tap3))
(setq coords (list 
(list 960.464 868.18) 
(list 960.4542 868.18) 
(list 960.4539 868.1903) 
(list 960.4525 868.2006) 
(list 960.4501 868.2108) 
(list 960.4466 868.2211) 
(list 960.4423 868.2314) 
(list 960.4371 868.2417) 
(list 960.4313 868.2519) 
(list 960.425 868.2622) 
(list 960.4184 868.2725) 
(list 960.4117 868.2828) 
(list 960.4052 868.2931) 
(list 960.399 868.3033) 
(list 960.3933 868.3136) 
(list 960.3883 868.3239) 
(list 960.3841 868.3342) 
(list 960.381 868.3444) 
(list 960.3789 868.3547) 
(list 960.3781 868.365) 
(list 960.3785 868.3753) 
(list 960.3801 868.3856) 
(list 960.3829 868.3958) 
(list 960.3869 868.4061) 
(list 960.3919 868.4164) 
(list 960.3977 868.4267) 
(list 960.4043 868.4369) 
(list 960.4114 868.4472) 
(list 960.4188 868.4575) 
(list 960.4263 868.4678) 
(list 960.4336 868.4781) 
(list 960.4406 868.4883) 
(list 960.447 868.4986) 
(list 960.4526 868.5089) 
(list 960.4573 868.5192) 
(list 960.4608 868.5294) 
(list 960.463 868.5397) 
(list 960.464 868.55) 
(list 960.464 868.55)))
(apply 'command (append '("pline") coords '("c")))
(setq tap3 (ssadd (entlast) tap3))
(command "_mirror" (entlast) "" "960,900" "960,901" "No")
(setq tap3 (ssadd (entlast) tap3))
(setq coords (list 
(list 961.124 868.18) 
(list 960.464 868.18) 
(list 960.464 868.1903) 
(list 960.464 868.2006) 
(list 960.464 868.2108) 
(list 960.464 868.2211) 
(list 960.464 868.2314) 
(list 960.464 868.2417) 
(list 960.464 868.2519) 
(list 960.464 868.2622) 
(list 960.464 868.2725) 
(list 960.464 868.2828) 
(list 960.464 868.2931) 
(list 960.464 868.3033) 
(list 960.464 868.3136) 
(list 960.464 868.3239) 
(list 960.464 868.3342) 
(list 960.464 868.3444) 
(list 960.464 868.3547) 
(list 960.464 868.365) 
(list 960.464 868.3753) 
(list 960.464 868.3856) 
(list 960.464 868.3958) 
(list 960.464 868.4061) 
(list 960.464 868.4164) 
(list 960.464 868.4267) 
(list 960.464 868.4369) 
(list 960.464 868.4472) 
(list 960.464 868.4575) 
(list 960.464 868.4678) 
(list 960.464 868.4781) 
(list 960.464 868.4883) 
(list 960.464 868.4986) 
(list 960.464 868.5089) 
(list 960.464 868.5192) 
(list 960.464 868.5294) 
(list 960.464 868.5397) 
(list 960.464 868.55) 
(list 961.124 868.55)))
(apply 'command (append '("pline") coords '("c")))
(setq tap3 (ssadd (entlast) tap3))
(command "_mirror" (entlast) "" "960,900" "960,901" "No")
(setq tap3 (ssadd (entlast) tap3))
(setq coords (list 
(list 960 868.55) 
(list 960.135 868.55) 
(list 960.135 868.5603) 
(list 960.135 868.5706) 
(list 960.135 868.5808) 
(list 960.135 868.5911) 
(list 960.135 868.6014) 
(list 960.135 868.6117) 
(list 960.135 868.6219) 
(list 960.135 868.6322) 
(list 960.135 868.6425) 
(list 960.135 868.6528) 
(list 960.135 868.6631) 
(list 960.135 868.6733) 
(list 960.135 868.6836) 
(list 960.135 868.6939) 
(list 960.135 868.7042) 
(list 960.135 868.7144) 
(list 960.135 868.7247) 
(list 960.135 868.735) 
(list 960.135 868.7453) 
(list 960.135 868.7556) 
(list 960.135 868.7658) 
(list 960.135 868.7761) 
(list 960.135 868.7864) 
(list 960.135 868.7967) 
(list 960.135 868.8069) 
(list 960.135 868.8172) 
(list 960.135 868.8275) 
(list 960.135 868.8378) 
(list 960.135 868.8481) 
(list 960.135 868.8583) 
(list 960.135 868.8686) 
(list 960.135 868.8789) 
(list 960.135 868.8892) 
(list 960.135 868.8994) 
(list 960.135 868.9097) 
(list 960.135 868.92) 
(list 960 868.92)))
(apply 'command (append '("pline") coords '("c")))
(setq tap3 (ssadd (entlast) tap3))
(command "_mirror" (entlast) "" "960,900" "960,901" "No")
(setq tap3 (ssadd (entlast) tap3))
(setq coords (list 
(list 960.4738 868.55) 
(list 960.464 868.55) 
(list 960.4636 868.5603) 
(list 960.4618 868.5706) 
(list 960.4587 868.5808) 
(list 960.4543 868.5911) 
(list 960.4488 868.6014) 
(list 960.4424 868.6117) 
(list 960.4351 868.6219) 
(list 960.4273 868.6322) 
(list 960.4192 868.6425) 
(list 960.411 868.6528) 
(list 960.4029 868.6631) 
(list 960.3953 868.6733) 
(list 960.3883 868.6836) 
(list 960.3822 868.6939) 
(list 960.3771 868.7042) 
(list 960.3733 868.7144) 
(list 960.3709 868.7247) 
(list 960.3699 868.735) 
(list 960.3704 868.7453) 
(list 960.3725 868.7556) 
(list 960.3759 868.7658) 
(list 960.3808 868.7761) 
(list 960.3869 868.7864) 
(list 960.394 868.7967) 
(list 960.402 868.8069) 
(list 960.4106 868.8172) 
(list 960.4196 868.8275) 
(list 960.4287 868.8378) 
(list 960.4375 868.8481) 
(list 960.4459 868.8583) 
(list 960.4536 868.8686) 
(list 960.4603 868.8789) 
(list 960.4658 868.8892) 
(list 960.47 868.8994) 
(list 960.4727 868.9097) 
(list 960.4738 868.92) 
(list 960.4738 868.92)))
(apply 'command (append '("pline") coords '("c")))
(setq tap3 (ssadd (entlast) tap3))
(command "_mirror" (entlast) "" "960,900" "960,901" "No")
(setq tap3 (ssadd (entlast) tap3))
(setq coords (list 
(list 961.124 868.55) 
(list 960.4738 868.55) 
(list 960.4738 868.5603) 
(list 960.4738 868.5706) 
(list 960.4738 868.5808) 
(list 960.4738 868.5911) 
(list 960.4738 868.6014) 
(list 960.4738 868.6117) 
(list 960.4738 868.6219) 
(list 960.4738 868.6322) 
(list 960.4738 868.6425) 
(list 960.4738 868.6528) 
(list 960.4738 868.6631) 
(list 960.4738 868.6733) 
(list 960.4738 868.6836) 
(list 960.4738 868.6939) 
(list 960.4738 868.7042) 
(list 960.4738 868.7144) 
(list 960.4738 868.7247) 
(list 960.4738 868.735) 
(list 960.4738 868.7453) 
(list 960.4738 868.7556) 
(list 960.4738 868.7658) 
(list 960.4738 868.7761) 
(list 960.4738 868.7864) 
(list 960.4738 868.7967) 
(list 960.4738 868.8069) 
(list 960.4738 868.8172) 
(list 960.4738 868.8275) 
(list 960.4738 868.8378) 
(list 960.4738 868.8481) 
(list 960.4738 868.8583) 
(list 960.4738 868.8686) 
(list 960.4738 868.8789) 
(list 960.4738 868.8892) 
(list 960.4738 868.8994) 
(list 960.4738 868.9097) 
(list 960.4738 868.92) 
(list 961.124 868.92)))
(apply 'command (append '("pline") coords '("c")))
(setq tap3 (ssadd (entlast) tap3))
(command "_mirror" (entlast) "" "960,900" "960,901" "No")
(setq tap3 (ssadd (entlast) tap3))
(setq coords (list 
(list 960 868.92) 
(list 960.135 868.92) 
(list 960.135 868.9303) 
(list 960.135 868.9406) 
(list 960.135 868.9508) 
(list 960.135 868.9611) 
(list 960.135 868.9714) 
(list 960.135 868.9817) 
(list 960.135 868.9919) 
(list 960.135 869.0022) 
(list 960.135 869.0125) 
(list 960.135 869.0228) 
(list 960.135 869.0331) 
(list 960.135 869.0433) 
(list 960.135 869.0536) 
(list 960.135 869.0639) 
(list 960.135 869.0742) 
(list 960.135 869.0844) 
(list 960.135 869.0947) 
(list 960.135 869.105) 
(list 960.135 869.1153) 
(list 960.135 869.1256) 
(list 960.135 869.1358) 
(list 960.135 869.1461) 
(list 960.135 869.1564) 
(list 960.135 869.1667) 
(list 960.135 869.1769) 
(list 960.135 869.1872) 
(list 960.135 869.1975) 
(list 960.135 869.2078) 
(list 960.135 869.2181) 
(list 960.135 869.2283) 
(list 960.135 869.2386) 
(list 960.135 869.2489) 
(list 960.135 869.2592) 
(list 960.135 869.2694) 
(list 960.135 869.2797) 
(list 960.135 869.29) 
(list 960 869.29)))
(apply 'command (append '("pline") coords '("c")))
(setq tap3 (ssadd (entlast) tap3))
(command "_mirror" (entlast) "" "960,900" "960,901" "No")
(setq tap3 (ssadd (entlast) tap3))
(setq coords (list 
(list 960.4836 868.92) 
(list 960.4738 868.92) 
(list 960.4732 868.9303) 
(list 960.4711 868.9406) 
(list 960.4673 868.9508) 
(list 960.462 868.9611) 
(list 960.4554 868.9714) 
(list 960.4477 868.9817) 
(list 960.439 868.9919) 
(list 960.4297 869.0022) 
(list 960.42 869.0125) 
(list 960.4102 869.0228) 
(list 960.4006 869.0331) 
(list 960.3916 869.0433) 
(list 960.3833 869.0536) 
(list 960.3761 869.0639) 
(list 960.3701 869.0742) 
(list 960.3657 869.0844) 
(list 960.3628 869.0947) 
(list 960.3617 869.105) 
(list 960.3624 869.1153) 
(list 960.3648 869.1256) 
(list 960.369 869.1358) 
(list 960.3747 869.1461) 
(list 960.3819 869.1564) 
(list 960.3903 869.1667) 
(list 960.3997 869.1769) 
(list 960.4099 869.1872) 
(list 960.4204 869.1975) 
(list 960.431 869.2078) 
(list 960.4414 869.2181) 
(list 960.4512 869.2283) 
(list 960.4602 869.2386) 
(list 960.468 869.2489) 
(list 960.4744 869.2592) 
(list 960.4793 869.2694) 
(list 960.4824 869.2797) 
(list 960.4836 869.29) 
(list 960.4836 869.29)))
(apply 'command (append '("pline") coords '("c")))
(setq tap3 (ssadd (entlast) tap3))
(command "_mirror" (entlast) "" "960,900" "960,901" "No")
(setq tap3 (ssadd (entlast) tap3))
(setq coords (list 
(list 961.124 868.92) 
(list 960.4836 868.92) 
(list 960.4836 868.9303) 
(list 960.4836 868.9406) 
(list 960.4836 868.9508) 
(list 960.4836 868.9611) 
(list 960.4836 868.9714) 
(list 960.4836 868.9817) 
(list 960.4836 868.9919) 
(list 960.4836 869.0022) 
(list 960.4836 869.0125) 
(list 960.4836 869.0228) 
(list 960.4836 869.0331) 
(list 960.4836 869.0433) 
(list 960.4836 869.0536) 
(list 960.4836 869.0639) 
(list 960.4836 869.0742) 
(list 960.4836 869.0844) 
(list 960.4836 869.0947) 
(list 960.4836 869.105) 
(list 960.4836 869.1153) 
(list 960.4836 869.1256) 
(list 960.4836 869.1358) 
(list 960.4836 869.1461) 
(list 960.4836 869.1564) 
(list 960.4836 869.1667) 
(list 960.4836 869.1769) 
(list 960.4836 869.1872) 
(list 960.4836 869.1975) 
(list 960.4836 869.2078) 
(list 960.4836 869.2181) 
(list 960.4836 869.2283) 
(list 960.4836 869.2386) 
(list 960.4836 869.2489) 
(list 960.4836 869.2592) 
(list 960.4836 869.2694) 
(list 960.4836 869.2797) 
(list 960.4836 869.29) 
(list 961.124 869.29)))
(apply 'command (append '("pline") coords '("c")))
(setq tap3 (ssadd (entlast) tap3))
(command "_mirror" (entlast) "" "960,900" "960,901" "No")
(setq tap3 (ssadd (entlast) tap3))
(setq coords (list 
(list 960 869.29) 
(list 960.135 869.29) 
(list 960.135 869.3003) 
(list 960.135 869.3106) 
(list 960.135 869.3208) 
(list 960.135 869.3311) 
(list 960.135 869.3414) 
(list 960.135 869.3517) 
(list 960.135 869.3619) 
(list 960.135 869.3722) 
(list 960.135 869.3825) 
(list 960.135 869.3928) 
(list 960.135 869.4031) 
(list 960.135 869.4133) 
(list 960.135 869.4236) 
(list 960.135 869.4339) 
(list 960.135 869.4442) 
(list 960.135 869.4544) 
(list 960.135 869.4647) 
(list 960.135 869.475) 
(list 960.135 869.4853) 
(list 960.135 869.4956) 
(list 960.135 869.5058) 
(list 960.135 869.5161) 
(list 960.135 869.5264) 
(list 960.135 869.5367) 
(list 960.135 869.5469) 
(list 960.135 869.5572) 
(list 960.135 869.5675) 
(list 960.135 869.5778) 
(list 960.135 869.5881) 
(list 960.135 869.5983) 
(list 960.135 869.6086) 
(list 960.135 869.6189) 
(list 960.135 869.6292) 
(list 960.135 869.6394) 
(list 960.135 869.6497) 
(list 960.135 869.66) 
(list 960 869.66)))
(apply 'command (append '("pline") coords '("c")))
(setq tap3 (ssadd (entlast) tap3))
(command "_mirror" (entlast) "" "960,900" "960,901" "No")
(setq tap3 (ssadd (entlast) tap3))
(setq coords (list 
(list 960.4934 869.29) 
(list 960.4836 869.29) 
(list 960.4829 869.3003) 
(list 960.4803 869.3106) 
(list 960.4759 869.3208) 
(list 960.4697 869.3311) 
(list 960.462 869.3414) 
(list 960.453 869.3517) 
(list 960.4429 869.3619) 
(list 960.4321 869.3722) 
(list 960.4208 869.3825) 
(list 960.4094 869.3928) 
(list 960.3984 869.4031) 
(list 960.3879 869.4133) 
(list 960.3783 869.4236) 
(list 960.37 869.4339) 
(list 960.3631 869.4442) 
(list 960.358 869.4544) 
(list 960.3547 869.4647) 
(list 960.3535 869.475) 
(list 960.3543 869.4853) 
(list 960.3571 869.4956) 
(list 960.362 869.5058) 
(list 960.3686 869.5161) 
(list 960.3769 869.5264) 
(list 960.3866 869.5367) 
(list 960.3975 869.5469) 
(list 960.4091 869.5572) 
(list 960.4212 869.5675) 
(list 960.4334 869.5778) 
(list 960.4453 869.5881) 
(list 960.4565 869.5983) 
(list 960.4668 869.6086) 
(list 960.4757 869.6189) 
(list 960.483 869.6292) 
(list 960.4885 869.6394) 
(list 960.492 869.6497) 
(list 960.4934 869.66) 
(list 960.4934 869.66)))
(apply 'command (append '("pline") coords '("c")))
(setq tap3 (ssadd (entlast) tap3))
(command "_mirror" (entlast) "" "960,900" "960,901" "No")
(setq tap3 (ssadd (entlast) tap3))
(setq coords (list 
(list 961.124 869.29) 
(list 960.4934 869.29) 
(list 960.4934 869.3003) 
(list 960.4934 869.3106) 
(list 960.4934 869.3208) 
(list 960.4934 869.3311) 
(list 960.4934 869.3414) 
(list 960.4934 869.3517) 
(list 960.4934 869.3619) 
(list 960.4934 869.3722) 
(list 960.4934 869.3825) 
(list 960.4934 869.3928) 
(list 960.4934 869.4031) 
(list 960.4934 869.4133) 
(list 960.4934 869.4236) 
(list 960.4934 869.4339) 
(list 960.4934 869.4442) 
(list 960.4934 869.4544) 
(list 960.4934 869.4647) 
(list 960.4934 869.475) 
(list 960.4934 869.4853) 
(list 960.4934 869.4956) 
(list 960.4934 869.5058) 
(list 960.4934 869.5161) 
(list 960.4934 869.5264) 
(list 960.4934 869.5367) 
(list 960.4934 869.5469) 
(list 960.4934 869.5572) 
(list 960.4934 869.5675) 
(list 960.4934 869.5778) 
(list 960.4934 869.5881) 
(list 960.4934 869.5983) 
(list 960.4934 869.6086) 
(list 960.4934 869.6189) 
(list 960.4934 869.6292) 
(list 960.4934 869.6394) 
(list 960.4934 869.6497) 
(list 960.4934 869.66) 
(list 961.124 869.66)))
(apply 'command (append '("pline") coords '("c")))
(setq tap3 (ssadd (entlast) tap3))
(command "_mirror" (entlast) "" "960,900" "960,901" "No")
(setq tap3 (ssadd (entlast) tap3))
(setq coords (list 
(list 960 869.66) 
(list 960.135 869.66) 
(list 960.135 869.6703) 
(list 960.135 869.6806) 
(list 960.135 869.6908) 
(list 960.135 869.7011) 
(list 960.135 869.7114) 
(list 960.135 869.7217) 
(list 960.135 869.7319) 
(list 960.135 869.7422) 
(list 960.135 869.7525) 
(list 960.135 869.7628) 
(list 960.135 869.7731) 
(list 960.135 869.7833) 
(list 960.135 869.7936) 
(list 960.135 869.8039) 
(list 960.135 869.8142) 
(list 960.135 869.8244) 
(list 960.135 869.8347) 
(list 960.135 869.845) 
(list 960.135 869.8553) 
(list 960.135 869.8656) 
(list 960.135 869.8758) 
(list 960.135 869.8861) 
(list 960.135 869.8964) 
(list 960.135 869.9067) 
(list 960.135 869.9169) 
(list 960.135 869.9272) 
(list 960.135 869.9375) 
(list 960.135 869.9478) 
(list 960.135 869.9581) 
(list 960.135 869.9683) 
(list 960.135 869.9786) 
(list 960.135 869.9889) 
(list 960.135 869.9992) 
(list 960.135 870.0094) 
(list 960.135 870.0197) 
(list 960.135 870.03) 
(list 960 870.03)))
(apply 'command (append '("pline") coords '("c")))
(setq tap3 (ssadd (entlast) tap3))
(command "_mirror" (entlast) "" "960,900" "960,901" "No")
(setq tap3 (ssadd (entlast) tap3))
(setq coords (list 
(list 960.5032 869.66) 
(list 960.4934 869.66) 
(list 960.4926 869.6703) 
(list 960.4896 869.6806) 
(list 960.4845 869.6908) 
(list 960.4774 869.7011) 
(list 960.4686 869.7114) 
(list 960.4583 869.7217) 
(list 960.4468 869.7319) 
(list 960.4344 869.7422) 
(list 960.4216 869.7525) 
(list 960.4087 869.7628) 
(list 960.3961 869.7731) 
(list 960.3842 869.7833) 
(list 960.3733 869.7936) 
(list 960.3639 869.8039) 
(list 960.3561 869.8142) 
(list 960.3503 869.8244) 
(list 960.3467 869.8347) 
(list 960.3453 869.845) 
(list 960.3462 869.8553) 
(list 960.3495 869.8656) 
(list 960.355 869.8758) 
(list 960.3625 869.8861) 
(list 960.3719 869.8964) 
(list 960.3829 869.9067) 
(list 960.3952 869.9169) 
(list 960.4083 869.9272) 
(list 960.422 869.9375) 
(list 960.4357 869.9478) 
(list 960.4492 869.9581) 
(list 960.4618 869.9683) 
(list 960.4734 869.9786) 
(list 960.4834 869.9889) 
(list 960.4916 869.9992) 
(list 960.4978 870.0094) 
(list 960.5017 870.0197) 
(list 960.5032 870.03) 
(list 960.5032 870.03)))
(apply 'command (append '("pline") coords '("c")))
(setq tap3 (ssadd (entlast) tap3))
(command "_mirror" (entlast) "" "960,900" "960,901" "No")
(setq tap3 (ssadd (entlast) tap3))
(setq coords (list 
(list 961.124 869.66) 
(list 960.5032 869.66) 
(list 960.5032 869.6703) 
(list 960.5032 869.6806) 
(list 960.5032 869.6908) 
(list 960.5032 869.7011) 
(list 960.5032 869.7114) 
(list 960.5032 869.7217) 
(list 960.5032 869.7319) 
(list 960.5032 869.7422) 
(list 960.5032 869.7525) 
(list 960.5032 869.7628) 
(list 960.5032 869.7731) 
(list 960.5032 869.7833) 
(list 960.5032 869.7936) 
(list 960.5032 869.8039) 
(list 960.5032 869.8142) 
(list 960.5032 869.8244) 
(list 960.5032 869.8347) 
(list 960.5032 869.845) 
(list 960.5032 869.8553) 
(list 960.5032 869.8656) 
(list 960.5032 869.8758) 
(list 960.5032 869.8861) 
(list 960.5032 869.8964) 
(list 960.5032 869.9067) 
(list 960.5032 869.9169) 
(list 960.5032 869.9272) 
(list 960.5032 869.9375) 
(list 960.5032 869.9478) 
(list 960.5032 869.9581) 
(list 960.5032 869.9683) 
(list 960.5032 869.9786) 
(list 960.5032 869.9889) 
(list 960.5032 869.9992) 
(list 960.5032 870.0094) 
(list 960.5032 870.0197) 
(list 960.5032 870.03) 
(list 961.124 870.03)))
(apply 'command (append '("pline") coords '("c")))
(setq tap3 (ssadd (entlast) tap3))
(command "_mirror" (entlast) "" "960,900" "960,901" "No")
(setq tap3 (ssadd (entlast) tap3))
(setq coords (list 
(list 960 870.03) 
(list 960.135 870.03) 
(list 960.135 870.0403) 
(list 960.135 870.0506) 
(list 960.135 870.0608) 
(list 960.135 870.0711) 
(list 960.135 870.0814) 
(list 960.135 870.0917) 
(list 960.135 870.1019) 
(list 960.135 870.1122) 
(list 960.135 870.1225) 
(list 960.135 870.1328) 
(list 960.135 870.1431) 
(list 960.135 870.1533) 
(list 960.135 870.1636) 
(list 960.135 870.1739) 
(list 960.135 870.1842) 
(list 960.135 870.1944) 
(list 960.135 870.2047) 
(list 960.135 870.215) 
(list 960.135 870.2253) 
(list 960.135 870.2356) 
(list 960.135 870.2458) 
(list 960.135 870.2561) 
(list 960.135 870.2664) 
(list 960.135 870.2767) 
(list 960.135 870.2869) 
(list 960.135 870.2972) 
(list 960.135 870.3075) 
(list 960.135 870.3178) 
(list 960.135 870.3281) 
(list 960.135 870.3383) 
(list 960.135 870.3486) 
(list 960.135 870.3589) 
(list 960.135 870.3692) 
(list 960.135 870.3794) 
(list 960.135 870.3897) 
(list 960.135 870.4) 
(list 960 870.4)))
(apply 'command (append '("pline") coords '("c")))
(setq tap3 (ssadd (entlast) tap3))
(command "_mirror" (entlast) "" "960,900" "960,901" "No")
(setq tap3 (ssadd (entlast) tap3))
(setq coords (list 
(list 960.513 870.03) 
(list 960.5032 870.03) 
(list 960.5022 870.0403) 
(list 960.4988 870.0506) 
(list 960.4931 870.0608) 
(list 960.4851 870.0711) 
(list 960.4752 870.0814) 
(list 960.4636 870.0917) 
(list 960.4507 870.1019) 
(list 960.4368 870.1122) 
(list 960.4224 870.1225) 
(list 960.4079 870.1328) 
(list 960.3938 870.1431) 
(list 960.3805 870.1533) 
(list 960.3683 870.1636) 
(list 960.3578 870.1739) 
(list 960.3491 870.1842) 
(list 960.3427 870.1944) 
(list 960.3386 870.2047) 
(list 960.3371 870.215) 
(list 960.3382 870.2253) 
(list 960.3418 870.2356) 
(list 960.348 870.2458) 
(list 960.3564 870.2561) 
(list 960.3669 870.2664) 
(list 960.3792 870.2767) 
(list 960.3929 870.2869) 
(list 960.4076 870.2972) 
(list 960.4228 870.3075) 
(list 960.4381 870.3178) 
(list 960.453 870.3281) 
(list 960.4671 870.3383) 
(list 960.4799 870.3486) 
(list 960.4911 870.3589) 
(list 960.5002 870.3692) 
(list 960.5071 870.3794) 
(list 960.5114 870.3897) 
(list 960.513 870.4) 
(list 960.513 870.4)))
(apply 'command (append '("pline") coords '("c")))
(setq tap3 (ssadd (entlast) tap3))
(command "_mirror" (entlast) "" "960,900" "960,901" "No")
(setq tap3 (ssadd (entlast) tap3))
(setq coords (list 
(list 961.124 870.03) 
(list 960.513 870.03) 
(list 960.513 870.0403) 
(list 960.513 870.0506) 
(list 960.513 870.0608) 
(list 960.513 870.0711) 
(list 960.513 870.0814) 
(list 960.513 870.0917) 
(list 960.513 870.1019) 
(list 960.513 870.1122) 
(list 960.513 870.1225) 
(list 960.513 870.1328) 
(list 960.513 870.1431) 
(list 960.513 870.1533) 
(list 960.513 870.1636) 
(list 960.513 870.1739) 
(list 960.513 870.1842) 
(list 960.513 870.1944) 
(list 960.513 870.2047) 
(list 960.513 870.215) 
(list 960.513 870.2253) 
(list 960.513 870.2356) 
(list 960.513 870.2458) 
(list 960.513 870.2561) 
(list 960.513 870.2664) 
(list 960.513 870.2767) 
(list 960.513 870.2869) 
(list 960.513 870.2972) 
(list 960.513 870.3075) 
(list 960.513 870.3178) 
(list 960.513 870.3281) 
(list 960.513 870.3383) 
(list 960.513 870.3486) 
(list 960.513 870.3589) 
(list 960.513 870.3692) 
(list 960.513 870.3794) 
(list 960.513 870.3897) 
(list 960.513 870.4) 
(list 961.124 870.4)))
(apply 'command (append '("pline") coords '("c")))
(setq tap3 (ssadd (entlast) tap3))
(command "_mirror" (entlast) "" "960,900" "960,901" "No")
(setq tap3 (ssadd (entlast) tap3))
(setq coords (list 
(list 960 870.4) 
(list 960.135 870.4) 
(list 960.135 870.4103) 
(list 960.135 870.4206) 
(list 960.135 870.4308) 
(list 960.135 870.4411) 
(list 960.135 870.4514) 
(list 960.135 870.4617) 
(list 960.135 870.4719) 
(list 960.135 870.4822) 
(list 960.135 870.4925) 
(list 960.135 870.5028) 
(list 960.135 870.5131) 
(list 960.135 870.5233) 
(list 960.135 870.5336) 
(list 960.135 870.5439) 
(list 960.135 870.5542) 
(list 960.135 870.5644) 
(list 960.135 870.5747) 
(list 960.135 870.585) 
(list 960.135 870.5953) 
(list 960.135 870.6056) 
(list 960.135 870.6158) 
(list 960.135 870.6261) 
(list 960.135 870.6364) 
(list 960.135 870.6467) 
(list 960.135 870.6569) 
(list 960.135 870.6672) 
(list 960.135 870.6775) 
(list 960.135 870.6878) 
(list 960.135 870.6981) 
(list 960.135 870.7083) 
(list 960.135 870.7186) 
(list 960.135 870.7289) 
(list 960.135 870.7392) 
(list 960.135 870.7494) 
(list 960.135 870.7597) 
(list 960.135 870.77) 
(list 960 870.77)))
(apply 'command (append '("pline") coords '("c")))
(setq tap3 (ssadd (entlast) tap3))
(command "_mirror" (entlast) "" "960,900" "960,901" "No")
(setq tap3 (ssadd (entlast) tap3))
(setq coords (list 
(list 960.5228 870.4) 
(list 960.513 870.4) 
(list 960.5119 870.4103) 
(list 960.5081 870.4206) 
(list 960.5017 870.4308) 
(list 960.4928 870.4411) 
(list 960.4818 870.4514) 
(list 960.4689 870.4617) 
(list 960.4545 870.4719) 
(list 960.4392 870.4822) 
(list 960.4232 870.4925) 
(list 960.4072 870.5028) 
(list 960.3915 870.5131) 
(list 960.3768 870.5233) 
(list 960.3633 870.5336) 
(list 960.3517 870.5439) 
(list 960.3421 870.5542) 
(list 960.335 870.5644) 
(list 960.3306 870.5747) 
(list 960.3289 870.585) 
(list 960.3301 870.5953) 
(list 960.3342 870.6056) 
(list 960.341 870.6158) 
(list 960.3503 870.6261) 
(list 960.362 870.6364) 
(list 960.3755 870.6467) 
(list 960.3906 870.6569) 
(list 960.4068 870.6672) 
(list 960.4236 870.6775) 
(list 960.4405 870.6878) 
(list 960.4569 870.6981) 
(list 960.4724 870.7083) 
(list 960.4865 870.7186) 
(list 960.4988 870.7289) 
(list 960.5088 870.7392) 
(list 960.5163 870.7494) 
(list 960.521 870.7597) 
(list 960.5228 870.77) 
(list 960.5228 870.77)))
(apply 'command (append '("pline") coords '("c")))
(setq tap3 (ssadd (entlast) tap3))
(command "_mirror" (entlast) "" "960,900" "960,901" "No")
(setq tap3 (ssadd (entlast) tap3))
(setq coords (list 
(list 961.124 870.4) 
(list 960.5228 870.4) 
(list 960.5228 870.4103) 
(list 960.5228 870.4206) 
(list 960.5228 870.4308) 
(list 960.5228 870.4411) 
(list 960.5228 870.4514) 
(list 960.5228 870.4617) 
(list 960.5228 870.4719) 
(list 960.5228 870.4822) 
(list 960.5228 870.4925) 
(list 960.5228 870.5028) 
(list 960.5228 870.5131) 
(list 960.5228 870.5233) 
(list 960.5228 870.5336) 
(list 960.5228 870.5439) 
(list 960.5228 870.5542) 
(list 960.5228 870.5644) 
(list 960.5228 870.5747) 
(list 960.5228 870.585) 
(list 960.5228 870.5953) 
(list 960.5228 870.6056) 
(list 960.5228 870.6158) 
(list 960.5228 870.6261) 
(list 960.5228 870.6364) 
(list 960.5228 870.6467) 
(list 960.5228 870.6569) 
(list 960.5228 870.6672) 
(list 960.5228 870.6775) 
(list 960.5228 870.6878) 
(list 960.5228 870.6981) 
(list 960.5228 870.7083) 
(list 960.5228 870.7186) 
(list 960.5228 870.7289) 
(list 960.5228 870.7392) 
(list 960.5228 870.7494) 
(list 960.5228 870.7597) 
(list 960.5228 870.77) 
(list 961.124 870.77)))
(apply 'command (append '("pline") coords '("c")))
(setq tap3 (ssadd (entlast) tap3))
(command "_mirror" (entlast) "" "960,900" "960,901" "No")
(setq tap3 (ssadd (entlast) tap3))
(setq coords (list 
(list 960 870.77) 
(list 960.135 870.77) 
(list 960.135 870.7803) 
(list 960.135 870.7906) 
(list 960.135 870.8008) 
(list 960.135 870.8111) 
(list 960.135 870.8214) 
(list 960.135 870.8317) 
(list 960.135 870.8419) 
(list 960.135 870.8522) 
(list 960.135 870.8625) 
(list 960.135 870.8728) 
(list 960.135 870.8831) 
(list 960.135 870.8933) 
(list 960.135 870.9036) 
(list 960.135 870.9139) 
(list 960.135 870.9242) 
(list 960.135 870.9344) 
(list 960.135 870.9447) 
(list 960.135 870.955) 
(list 960.135 870.9653) 
(list 960.135 870.9756) 
(list 960.135 870.9858) 
(list 960.135 870.9961) 
(list 960.135 871.0064) 
(list 960.135 871.0167) 
(list 960.135 871.0269) 
(list 960.135 871.0372) 
(list 960.135 871.0475) 
(list 960.135 871.0578) 
(list 960.135 871.0681) 
(list 960.135 871.0783) 
(list 960.135 871.0886) 
(list 960.135 871.0989) 
(list 960.135 871.1092) 
(list 960.135 871.1194) 
(list 960.135 871.1297) 
(list 960.135 871.14) 
(list 960 871.14)))
(apply 'command (append '("pline") coords '("c")))
(setq tap3 (ssadd (entlast) tap3))
(command "_mirror" (entlast) "" "960,900" "960,901" "No")
(setq tap3 (ssadd (entlast) tap3))
(setq coords (list 
(list 960.5326 870.77) 
(list 960.5228 870.77) 
(list 960.5216 870.7803) 
(list 960.5173 870.7906) 
(list 960.5103 870.8008) 
(list 960.5005 870.8111) 
(list 960.4884 870.8214) 
(list 960.4742 870.8317) 
(list 960.4584 870.8419) 
(list 960.4415 870.8522) 
(list 960.424 870.8625) 
(list 960.4064 870.8728) 
(list 960.3892 870.8831) 
(list 960.3731 870.8933) 
(list 960.3584 870.9036) 
(list 960.3456 870.9139) 
(list 960.3351 870.9242) 
(list 960.3274 870.9344) 
(list 960.3225 870.9447) 
(list 960.3207 870.955) 
(list 960.322 870.9653) 
(list 960.3265 870.9756) 
(list 960.334 870.9858) 
(list 960.3442 870.9961) 
(list 960.357 871.0064) 
(list 960.3718 871.0167) 
(list 960.3884 871.0269) 
(list 960.4061 871.0372) 
(list 960.4244 871.0475) 
(list 960.4428 871.0578) 
(list 960.4608 871.0681) 
(list 960.4777 871.0783) 
(list 960.4931 871.0886) 
(list 960.5065 871.0989) 
(list 960.5174 871.1092) 
(list 960.5256 871.1194) 
(list 960.5307 871.1297) 
(list 960.5326 871.14) 
(list 960.5326 871.14)))
(apply 'command (append '("pline") coords '("c")))
(setq tap3 (ssadd (entlast) tap3))
(command "_mirror" (entlast) "" "960,900" "960,901" "No")
(setq tap3 (ssadd (entlast) tap3))
(setq coords (list 
(list 961.124 870.77) 
(list 960.5326 870.77) 
(list 960.5326 870.7803) 
(list 960.5326 870.7906) 
(list 960.5326 870.8008) 
(list 960.5326 870.8111) 
(list 960.5326 870.8214) 
(list 960.5326 870.8317) 
(list 960.5326 870.8419) 
(list 960.5326 870.8522) 
(list 960.5326 870.8625) 
(list 960.5326 870.8728) 
(list 960.5326 870.8831) 
(list 960.5326 870.8933) 
(list 960.5326 870.9036) 
(list 960.5326 870.9139) 
(list 960.5326 870.9242) 
(list 960.5326 870.9344) 
(list 960.5326 870.9447) 
(list 960.5326 870.955) 
(list 960.5326 870.9653) 
(list 960.5326 870.9756) 
(list 960.5326 870.9858) 
(list 960.5326 870.9961) 
(list 960.5326 871.0064) 
(list 960.5326 871.0167) 
(list 960.5326 871.0269) 
(list 960.5326 871.0372) 
(list 960.5326 871.0475) 
(list 960.5326 871.0578) 
(list 960.5326 871.0681) 
(list 960.5326 871.0783) 
(list 960.5326 871.0886) 
(list 960.5326 871.0989) 
(list 960.5326 871.1092) 
(list 960.5326 871.1194) 
(list 960.5326 871.1297) 
(list 960.5326 871.14) 
(list 961.124 871.14)))
(apply 'command (append '("pline") coords '("c")))
(setq tap3 (ssadd (entlast) tap3))
(command "_mirror" (entlast) "" "960,900" "960,901" "No")
(setq tap3 (ssadd (entlast) tap3))
(setq coords (list 
(list 960 871.14) 
(list 960.135 871.14) 
(list 960.135 871.1503) 
(list 960.135 871.1606) 
(list 960.135 871.1708) 
(list 960.135 871.1811) 
(list 960.135 871.1914) 
(list 960.135 871.2017) 
(list 960.135 871.2119) 
(list 960.135 871.2222) 
(list 960.135 871.2325) 
(list 960.135 871.2428) 
(list 960.135 871.2531) 
(list 960.135 871.2633) 
(list 960.135 871.2736) 
(list 960.135 871.2839) 
(list 960.135 871.2942) 
(list 960.135 871.3044) 
(list 960.135 871.3147) 
(list 960.135 871.325) 
(list 960.135 871.3353) 
(list 960.135 871.3456) 
(list 960.135 871.3558) 
(list 960.135 871.3661) 
(list 960.135 871.3764) 
(list 960.135 871.3867) 
(list 960.135 871.3969) 
(list 960.135 871.4072) 
(list 960.135 871.4175) 
(list 960.135 871.4278) 
(list 960.135 871.4381) 
(list 960.135 871.4483) 
(list 960.135 871.4586) 
(list 960.135 871.4689) 
(list 960.135 871.4792) 
(list 960.135 871.4894) 
(list 960.135 871.4997) 
(list 960.135 871.51) 
(list 960 871.51)))
(apply 'command (append '("pline") coords '("c")))
(setq tap3 (ssadd (entlast) tap3))
(command "_mirror" (entlast) "" "960,900" "960,901" "No")
(setq tap3 (ssadd (entlast) tap3))
(setq coords (list 
(list 960.5424 871.14) 
(list 960.5326 871.14) 
(list 960.5312 871.1503) 
(list 960.5266 871.1606) 
(list 960.5188 871.1708) 
(list 960.5082 871.1811) 
(list 960.4949 871.1914) 
(list 960.4795 871.2017) 
(list 960.4623 871.2119) 
(list 960.4439 871.2222) 
(list 960.4248 871.2325) 
(list 960.4056 871.2428) 
(list 960.387 871.2531) 
(list 960.3694 871.2633) 
(list 960.3534 871.2736) 
(list 960.3395 871.2839) 
(list 960.3282 871.2942) 
(list 960.3197 871.3044) 
(list 960.3144 871.3147) 
(list 960.3125 871.325) 
(list 960.314 871.3353) 
(list 960.3189 871.3456) 
(list 960.327 871.3558) 
(list 960.3381 871.3661) 
(list 960.352 871.3764) 
(list 960.3681 871.3867) 
(list 960.3861 871.3969) 
(list 960.4053 871.4072) 
(list 960.4252 871.4175) 
(list 960.4452 871.4278) 
(list 960.4647 871.4381) 
(list 960.483 871.4483) 
(list 960.4997 871.4586) 
(list 960.5142 871.4689) 
(list 960.526 871.4792) 
(list 960.5348 871.4894) 
(list 960.5404 871.4997) 
(list 960.5424 871.51) 
(list 960.5424 871.51)))
(apply 'command (append '("pline") coords '("c")))
(setq tap3 (ssadd (entlast) tap3))
(command "_mirror" (entlast) "" "960,900" "960,901" "No")
(setq tap3 (ssadd (entlast) tap3))
(setq coords (list 
(list 961.124 871.14) 
(list 960.5424 871.14) 
(list 960.5424 871.1503) 
(list 960.5424 871.1606) 
(list 960.5424 871.1708) 
(list 960.5424 871.1811) 
(list 960.5424 871.1914) 
(list 960.5424 871.2017) 
(list 960.5424 871.2119) 
(list 960.5424 871.2222) 
(list 960.5424 871.2325) 
(list 960.5424 871.2428) 
(list 960.5424 871.2531) 
(list 960.5424 871.2633) 
(list 960.5424 871.2736) 
(list 960.5424 871.2839) 
(list 960.5424 871.2942) 
(list 960.5424 871.3044) 
(list 960.5424 871.3147) 
(list 960.5424 871.325) 
(list 960.5424 871.3353) 
(list 960.5424 871.3456) 
(list 960.5424 871.3558) 
(list 960.5424 871.3661) 
(list 960.5424 871.3764) 
(list 960.5424 871.3867) 
(list 960.5424 871.3969) 
(list 960.5424 871.4072) 
(list 960.5424 871.4175) 
(list 960.5424 871.4278) 
(list 960.5424 871.4381) 
(list 960.5424 871.4483) 
(list 960.5424 871.4586) 
(list 960.5424 871.4689) 
(list 960.5424 871.4792) 
(list 960.5424 871.4894) 
(list 960.5424 871.4997) 
(list 960.5424 871.51) 
(list 961.124 871.51)))
(apply 'command (append '("pline") coords '("c")))
(setq tap3 (ssadd (entlast) tap3))
(command "_mirror" (entlast) "" "960,900" "960,901" "No")
(setq tap3 (ssadd (entlast) tap3))
(setq coords (list 
(list 960 871.51) 
(list 960.135 871.51) 
(list 960.135 871.5203) 
(list 960.135 871.5306) 
(list 960.135 871.5408) 
(list 960.135 871.5511) 
(list 960.135 871.5614) 
(list 960.135 871.5717) 
(list 960.135 871.5819) 
(list 960.135 871.5922) 
(list 960.135 871.6025) 
(list 960.135 871.6128) 
(list 960.135 871.6231) 
(list 960.135 871.6333) 
(list 960.135 871.6436) 
(list 960.135 871.6539) 
(list 960.135 871.6642) 
(list 960.135 871.6744) 
(list 960.135 871.6847) 
(list 960.135 871.695) 
(list 960.135 871.7053) 
(list 960.135 871.7156) 
(list 960.135 871.7258) 
(list 960.135 871.7361) 
(list 960.135 871.7464) 
(list 960.135 871.7567) 
(list 960.135 871.7669) 
(list 960.135 871.7772) 
(list 960.135 871.7875) 
(list 960.135 871.7978) 
(list 960.135 871.8081) 
(list 960.135 871.8183) 
(list 960.135 871.8286) 
(list 960.135 871.8389) 
(list 960.135 871.8492) 
(list 960.135 871.8594) 
(list 960.135 871.8697) 
(list 960.135 871.88) 
(list 960 871.88)))
(apply 'command (append '("pline") coords '("c")))
(setq tap3 (ssadd (entlast) tap3))
(command "_mirror" (entlast) "" "960,900" "960,901" "No")
(setq tap3 (ssadd (entlast) tap3))
(setq coords (list 
(list 960.5522 871.51) 
(list 960.5424 871.51) 
(list 960.5409 871.5203) 
(list 960.5359 871.5306) 
(list 960.5274 871.5408) 
(list 960.5159 871.5511) 
(list 960.5015 871.5614) 
(list 960.4848 871.5717) 
(list 960.4662 871.5819) 
(list 960.4462 871.5922) 
(list 960.4256 871.6025) 
(list 960.4049 871.6128) 
(list 960.3847 871.6231) 
(list 960.3657 871.6333) 
(list 960.3484 871.6436) 
(list 960.3334 871.6539) 
(list 960.3212 871.6642) 
(list 960.3121 871.6744) 
(list 960.3064 871.6847) 
(list 960.3043 871.695) 
(list 960.3059 871.7053) 
(list 960.3112 871.7156) 
(list 960.32 871.7258) 
(list 960.332 871.7361) 
(list 960.347 871.7464) 
(list 960.3644 871.7567) 
(list 960.3838 871.7669) 
(list 960.4045 871.7772) 
(list 960.426 871.7875) 
(list 960.4476 871.7978) 
(list 960.4685 871.8081) 
(list 960.4883 871.8183) 
(list 960.5063 871.8286) 
(list 960.5219 871.8389) 
(list 960.5346 871.8492) 
(list 960.5441 871.8594) 
(list 960.55 871.8697) 
(list 960.5522 871.88) 
(list 960.5522 871.88)))
(apply 'command (append '("pline") coords '("c")))
(setq tap3 (ssadd (entlast) tap3))
(command "_mirror" (entlast) "" "960,900" "960,901" "No")
(setq tap3 (ssadd (entlast) tap3))
(setq coords (list 
(list 961.124 871.51) 
(list 960.5522 871.51) 
(list 960.5522 871.5203) 
(list 960.5522 871.5306) 
(list 960.5522 871.5408) 
(list 960.5522 871.5511) 
(list 960.5522 871.5614) 
(list 960.5522 871.5717) 
(list 960.5522 871.5819) 
(list 960.5522 871.5922) 
(list 960.5522 871.6025) 
(list 960.5522 871.6128) 
(list 960.5522 871.6231) 
(list 960.5522 871.6333) 
(list 960.5522 871.6436) 
(list 960.5522 871.6539) 
(list 960.5522 871.6642) 
(list 960.5522 871.6744) 
(list 960.5522 871.6847) 
(list 960.5522 871.695) 
(list 960.5522 871.7053) 
(list 960.5522 871.7156) 
(list 960.5522 871.7258) 
(list 960.5522 871.7361) 
(list 960.5522 871.7464) 
(list 960.5522 871.7567) 
(list 960.5522 871.7669) 
(list 960.5522 871.7772) 
(list 960.5522 871.7875) 
(list 960.5522 871.7978) 
(list 960.5522 871.8081) 
(list 960.5522 871.8183) 
(list 960.5522 871.8286) 
(list 960.5522 871.8389) 
(list 960.5522 871.8492) 
(list 960.5522 871.8594) 
(list 960.5522 871.8697) 
(list 960.5522 871.88) 
(list 961.124 871.88)))
(apply 'command (append '("pline") coords '("c")))
(setq tap3 (ssadd (entlast) tap3))
(command "_mirror" (entlast) "" "960,900" "960,901" "No")
(setq tap3 (ssadd (entlast) tap3))
(setq coords (list 
(list 960 871.88) 
(list 960.135 871.88) 
(list 960.135 871.8903) 
(list 960.135 871.9006) 
(list 960.135 871.9108) 
(list 960.135 871.9211) 
(list 960.135 871.9314) 
(list 960.135 871.9417) 
(list 960.135 871.9519) 
(list 960.135 871.9622) 
(list 960.135 871.9725) 
(list 960.135 871.9828) 
(list 960.135 871.9931) 
(list 960.135 872.0033) 
(list 960.135 872.0136) 
(list 960.135 872.0239) 
(list 960.135 872.0342) 
(list 960.135 872.0444) 
(list 960.135 872.0547) 
(list 960.135 872.065) 
(list 960.135 872.0753) 
(list 960.135 872.0856) 
(list 960.135 872.0958) 
(list 960.135 872.1061) 
(list 960.135 872.1164) 
(list 960.135 872.1267) 
(list 960.135 872.1369) 
(list 960.135 872.1472) 
(list 960.135 872.1575) 
(list 960.135 872.1678) 
(list 960.135 872.1781) 
(list 960.135 872.1883) 
(list 960.135 872.1986) 
(list 960.135 872.2089) 
(list 960.135 872.2192) 
(list 960.135 872.2294) 
(list 960.135 872.2397) 
(list 960.135 872.25) 
(list 960 872.25)))
(apply 'command (append '("pline") coords '("c")))
(setq tap3 (ssadd (entlast) tap3))
(command "_mirror" (entlast) "" "960,900" "960,901" "No")
(setq tap3 (ssadd (entlast) tap3))
(setq coords (list 
(list 960.562 871.88) 
(list 960.5522 871.88) 
(list 960.5506 871.8903) 
(list 960.5451 871.9006) 
(list 960.536 871.9108) 
(list 960.5236 871.9211) 
(list 960.5081 871.9314) 
(list 960.4901 871.9417) 
(list 960.47 871.9519) 
(list 960.4486 871.9622) 
(list 960.4264 871.9725) 
(list 960.4041 871.9828) 
(list 960.3824 871.9931) 
(list 960.362 872.0033) 
(list 960.3434 872.0136) 
(list 960.3273 872.0239) 
(list 960.3142 872.0342) 
(list 960.3044 872.0444) 
(list 960.2983 872.0547) 
(list 960.2961 872.065) 
(list 960.2979 872.0753) 
(list 960.3035 872.0856) 
(list 960.313 872.0958) 
(list 960.326 872.1061) 
(list 960.342 872.1164) 
(list 960.3607 872.1267) 
(list 960.3815 872.1369) 
(list 960.4038 872.1472) 
(list 960.4268 872.1575) 
(list 960.4499 872.1678) 
(list 960.4724 872.1781) 
(list 960.4936 872.1883) 
(list 960.5129 872.1986) 
(list 960.5296 872.2089) 
(list 960.5432 872.2192) 
(list 960.5533 872.2294) 
(list 960.5597 872.2397) 
(list 960.562 872.25) 
(list 960.562 872.25)))
(apply 'command (append '("pline") coords '("c")))
(setq tap3 (ssadd (entlast) tap3))
(command "_mirror" (entlast) "" "960,900" "960,901" "No")
(setq tap3 (ssadd (entlast) tap3))
(setq coords (list 
(list 961.124 871.88) 
(list 960.562 871.88) 
(list 960.562 871.8903) 
(list 960.562 871.9006) 
(list 960.562 871.9108) 
(list 960.562 871.9211) 
(list 960.562 871.9314) 
(list 960.562 871.9417) 
(list 960.562 871.9519) 
(list 960.562 871.9622) 
(list 960.562 871.9725) 
(list 960.562 871.9828) 
(list 960.562 871.9931) 
(list 960.562 872.0033) 
(list 960.562 872.0136) 
(list 960.562 872.0239) 
(list 960.562 872.0342) 
(list 960.562 872.0444) 
(list 960.562 872.0547) 
(list 960.562 872.065) 
(list 960.562 872.0753) 
(list 960.562 872.0856) 
(list 960.562 872.0958) 
(list 960.562 872.1061) 
(list 960.562 872.1164) 
(list 960.562 872.1267) 
(list 960.562 872.1369) 
(list 960.562 872.1472) 
(list 960.562 872.1575) 
(list 960.562 872.1678) 
(list 960.562 872.1781) 
(list 960.562 872.1883) 
(list 960.562 872.1986) 
(list 960.562 872.2089) 
(list 960.562 872.2192) 
(list 960.562 872.2294) 
(list 960.562 872.2397) 
(list 960.562 872.25) 
(list 961.124 872.25)))
(apply 'command (append '("pline") coords '("c")))
(setq tap3 (ssadd (entlast) tap3))
(command "_mirror" (entlast) "" "960,900" "960,901" "No")
(setq tap3 (ssadd (entlast) tap3))
(command "_block" "blktap3" "960,900" tap3 "")
(command "_insert" "blktap3" "960,900" "1" "1" "0")
(command "_insert" "blktap3" "960,900" "1" "1" "180")
(setq uc3 nil)
(setq uc3 (ssadd))
(setq coords (list 
(list 0 -0.185) 
(list 0.135 -0.185) 
(list 0.135 -0.17472) 
(list 0.135 -0.16444) 
(list 0.135 -0.15417) 
(list 0.135 -0.14389) 
(list 0.135 -0.13361) 
(list 0.135 -0.12333) 
(list 0.135 -0.11306) 
(list 0.135 -0.10278) 
(list 0.135 -0.0925) 
(list 0.135 -0.082222) 
(list 0.135 -0.071944) 
(list 0.135 -0.061667) 
(list 0.135 -0.051389) 
(list 0.135 -0.041111) 
(list 0.135 -0.030833) 
(list 0.135 -0.020556) 
(list 0.135 -0.010278) 
(list 0.135 0) 
(list 0.135 0.010278) 
(list 0.135 0.020556) 
(list 0.135 0.030833) 
(list 0.135 0.041111) 
(list 0.135 0.051389) 
(list 0.135 0.061667) 
(list 0.135 0.071944) 
(list 0.135 0.082222) 
(list 0.135 0.0925) 
(list 0.135 0.10278) 
(list 0.135 0.11306) 
(list 0.135 0.12333) 
(list 0.135 0.13361) 
(list 0.135 0.14389) 
(list 0.135 0.15417) 
(list 0.135 0.16444) 
(list 0.135 0.17472) 
(list 0.135 0.185) 
(list 0 0.185)))
(apply 'command (append '("pline") coords '("c")))
(setq uc3 (ssadd (entlast) uc3))
(setq coords (list 
(list 1.124 -0.185) 
(list 0.562 -0.185) 
(list 0.55995 -0.17472) 
(list 0.55386 -0.16444) 
(list 0.54391 -0.15417) 
(list 0.53042 -0.14389) 
(list 0.51378 -0.13361) 
(list 0.4945 -0.12333) 
(list 0.47317 -0.11306) 
(list 0.45044 -0.10278) 
(list 0.427 -0.0925) 
(list 0.40356 -0.082222) 
(list 0.38083 -0.071944) 
(list 0.3595 -0.061667) 
(list 0.34022 -0.051389) 
(list 0.32358 -0.041111) 
(list 0.31009 -0.030833) 
(list 0.30014 -0.020556) 
(list 0.29405 -0.010278) 
(list 0.292 0) 
(list 0.29405 0.010278) 
(list 0.30014 0.020556) 
(list 0.31009 0.030833) 
(list 0.32358 0.041111) 
(list 0.34022 0.051389) 
(list 0.3595 0.061667) 
(list 0.38083 0.071944) 
(list 0.40356 0.082222) 
(list 0.427 0.0925) 
(list 0.45044 0.10278) 
(list 0.47317 0.11306) 
(list 0.4945 0.12333) 
(list 0.51378 0.13361) 
(list 0.53042 0.14389) 
(list 0.54391 0.15417) 
(list 0.55386 0.16444) 
(list 0.55995 0.17472) 
(list 0.562 0.185) 
(list 1.124 0.185)))
(apply 'command (append '("pline") coords '("c")))
(setq uc3 (ssadd (entlast) uc3))
(command "_block" "blkuc3" "0,0.185" uc3 "")
(command "_insert" "blkuc3" "960,872.62" "1" "1" "0")
(command "_insert" "blkuc3" "960,872.25" "1" "1" "180")
(command "_insert" "blkuc3" "960,872.99" "1" "1" "0")
(command "_insert" "blkuc3" "960,872.62" "1" "1" "180")
(command "_insert" "blkuc3" "960,873.36" "1" "1" "0")
(command "_insert" "blkuc3" "960,872.99" "1" "1" "180")
(command "_insert" "blkuc3" "960,873.73" "1" "1" "0")
(command "_insert" "blkuc3" "960,873.36" "1" "1" "180")
(command "_insert" "blkuc3" "960,874.1" "1" "1" "0")
(command "_insert" "blkuc3" "960,873.73" "1" "1" "180")
(command "_insert" "blkuc3" "960,874.47" "1" "1" "0")
(command "_insert" "blkuc3" "960,874.1" "1" "1" "180")
(command "_insert" "blkuc3" "960,874.84" "1" "1" "0")
(command "_insert" "blkuc3" "960,874.47" "1" "1" "180")
(command "_insert" "blkuc3" "960,875.21" "1" "1" "0")
(command "_insert" "blkuc3" "960,874.84" "1" "1" "180")
(command "_insert" "blkuc3" "960,875.58" "1" "1" "0")
(command "_insert" "blkuc3" "960,875.21" "1" "1" "180")
(command "_insert" "blkuc3" "960,875.95" "1" "1" "0")
(command "_insert" "blkuc3" "960,875.58" "1" "1" "180")
(command "_insert" "blkuc3" "960,876.32" "1" "1" "0")
(command "_insert" "blkuc3" "960,875.95" "1" "1" "180")
(command "_insert" "blkuc3" "960,876.69" "1" "1" "0")
(command "_insert" "blkuc3" "960,876.32" "1" "1" "180")
(command "_insert" "blkuc3" "960,877.06" "1" "1" "0")
(command "_insert" "blkuc3" "960,876.69" "1" "1" "180")
(command "_insert" "blkuc3" "960,877.43" "1" "1" "0")
(command "_insert" "blkuc3" "960,877.06" "1" "1" "180")
(command "_insert" "blkuc3" "960,877.8" "1" "1" "0")
(command "_insert" "blkuc3" "960,877.43" "1" "1" "180")
(command "_insert" "blkuc3" "960,878.17" "1" "1" "0")
(command "_insert" "blkuc3" "960,877.8" "1" "1" "180")
(command "_insert" "blkuc3" "960,878.54" "1" "1" "0")
(command "_insert" "blkuc3" "960,878.17" "1" "1" "180")
(command "_insert" "blkuc3" "960,878.91" "1" "1" "0")
(command "_insert" "blkuc3" "960,878.54" "1" "1" "180")
(command "_insert" "blkuc3" "960,879.28" "1" "1" "0")
(command "_insert" "blkuc3" "960,878.91" "1" "1" "180")
(command "_insert" "blkuc3" "960,879.65" "1" "1" "0")
(command "_insert" "blkuc3" "960,879.28" "1" "1" "180")
(command "_insert" "blkuc3" "960,880.02" "1" "1" "0")
(command "_insert" "blkuc3" "960,879.65" "1" "1" "180")
(command "_insert" "blkuc3" "960,880.39" "1" "1" "0")
(command "_insert" "blkuc3" "960,880.02" "1" "1" "180")
(command "_insert" "blkuc3" "960,880.76" "1" "1" "0")
(command "_insert" "blkuc3" "960,880.39" "1" "1" "180")
(command "_insert" "blkuc3" "960,881.13" "1" "1" "0")
(command "_insert" "blkuc3" "960,880.76" "1" "1" "180")
(command "_insert" "blkuc3" "960,881.5" "1" "1" "0")
(command "_insert" "blkuc3" "960,881.13" "1" "1" "180")
(command "_insert" "blkuc3" "960,881.87" "1" "1" "0")
(command "_insert" "blkuc3" "960,881.5" "1" "1" "180")
(command "_insert" "blkuc3" "960,882.24" "1" "1" "0")
(command "_insert" "blkuc3" "960,881.87" "1" "1" "180")
(command "_insert" "blkuc3" "960,882.61" "1" "1" "0")
(command "_insert" "blkuc3" "960,882.24" "1" "1" "180")
(command "_insert" "blkuc3" "960,882.98" "1" "1" "0")
(command "_insert" "blkuc3" "960,882.61" "1" "1" "180")
(command "_insert" "blkuc3" "960,883.35" "1" "1" "0")
(command "_insert" "blkuc3" "960,882.98" "1" "1" "180")
(command "_insert" "blkuc3" "960,883.72" "1" "1" "0")
(command "_insert" "blkuc3" "960,883.35" "1" "1" "180")
(command "_insert" "blkuc3" "960,884.09" "1" "1" "0")
(command "_insert" "blkuc3" "960,883.72" "1" "1" "180")
(command "_insert" "blkuc3" "960,884.46" "1" "1" "0")
(command "_insert" "blkuc3" "960,884.09" "1" "1" "180")
(command "_insert" "blkuc3" "960,884.83" "1" "1" "0")
(command "_insert" "blkuc3" "960,884.46" "1" "1" "180")
(command "_insert" "blkuc3" "960,885.2" "1" "1" "0")
(command "_insert" "blkuc3" "960,884.83" "1" "1" "180")
(command "_insert" "blkuc3" "960,885.57" "1" "1" "0")
(command "_insert" "blkuc3" "960,885.2" "1" "1" "180")
(command "_insert" "blkuc3" "960,885.94" "1" "1" "0")
(command "_insert" "blkuc3" "960,885.57" "1" "1" "180")
(command "_insert" "blkuc3" "960,886.31" "1" "1" "0")
(command "_insert" "blkuc3" "960,885.94" "1" "1" "180")
(command "_insert" "blkuc3" "960,886.68" "1" "1" "0")
(command "_insert" "blkuc3" "960,886.31" "1" "1" "180")
(command "_insert" "blkuc3" "960,887.05" "1" "1" "0")
(command "_insert" "blkuc3" "960,886.68" "1" "1" "180")
(command "_insert" "blkuc3" "960,887.42" "1" "1" "0")
(command "_insert" "blkuc3" "960,887.05" "1" "1" "180")
(command "_insert" "blkuc3" "960,887.79" "1" "1" "0")
(command "_insert" "blkuc3" "960,887.42" "1" "1" "180")
(command "_insert" "blkuc3" "960,888.16" "1" "1" "0")
(command "_insert" "blkuc3" "960,887.79" "1" "1" "180")
(command "_insert" "blkuc3" "960,888.53" "1" "1" "0")
(command "_insert" "blkuc3" "960,888.16" "1" "1" "180")
(command "_insert" "blkuc3" "960,888.9" "1" "1" "0")
(command "_insert" "blkuc3" "960,888.53" "1" "1" "180")
(command "_insert" "blkuc3" "960,889.27" "1" "1" "0")
(command "_insert" "blkuc3" "960,888.9" "1" "1" "180")
(command "_insert" "blkuc3" "960,889.64" "1" "1" "0")
(command "_insert" "blkuc3" "960,889.27" "1" "1" "180")
(command "_insert" "blkuc3" "960,890.01" "1" "1" "0")
(command "_insert" "blkuc3" "960,889.64" "1" "1" "180")
(command "_insert" "blkuc3" "960,890.38" "1" "1" "0")
(command "_insert" "blkuc3" "960,890.01" "1" "1" "180")
(command "_insert" "blkuc3" "960,890.75" "1" "1" "0")
(command "_insert" "blkuc3" "960,890.38" "1" "1" "180")
(command "_insert" "blkuc3" "960,891.12" "1" "1" "0")
(command "_insert" "blkuc3" "960,890.75" "1" "1" "180")
(command "_insert" "blkuc3" "960,891.49" "1" "1" "0")
(command "_insert" "blkuc3" "960,891.12" "1" "1" "180")
(command "_insert" "blkuc3" "960,891.86" "1" "1" "0")
(command "_insert" "blkuc3" "960,891.49" "1" "1" "180")
(command "_insert" "blkuc3" "960,892.23" "1" "1" "0")
(command "_insert" "blkuc3" "960,891.86" "1" "1" "180")
(command "_insert" "blkuc3" "960,892.6" "1" "1" "0")
(command "_insert" "blkuc3" "960,892.23" "1" "1" "180")
(command "_insert" "blkuc3" "960,892.97" "1" "1" "0")
(command "_insert" "blkuc3" "960,892.6" "1" "1" "180")
(command "_insert" "blkuc3" "960,893.34" "1" "1" "0")
(command "_insert" "blkuc3" "960,892.97" "1" "1" "180")
(command "_insert" "blkuc3" "960,893.71" "1" "1" "0")
(command "_insert" "blkuc3" "960,893.34" "1" "1" "180")
(command "_insert" "blkuc3" "960,894.08" "1" "1" "0")
(command "_insert" "blkuc3" "960,893.71" "1" "1" "180")
(command "_insert" "blkuc3" "960,894.45" "1" "1" "0")
(command "_insert" "blkuc3" "960,894.08" "1" "1" "180")
(command "_insert" "blkuc3" "960,894.82" "1" "1" "0")
(command "_insert" "blkuc3" "960,894.45" "1" "1" "180")
(command "_insert" "blkuc3" "960,895.19" "1" "1" "0")
(command "_insert" "blkuc3" "960,894.82" "1" "1" "180")
(command "_insert" "blkuc3" "960,895.56" "1" "1" "0")
(command "_insert" "blkuc3" "960,895.19" "1" "1" "180")
(command "_insert" "blkuc3" "960,895.93" "1" "1" "0")
(command "_insert" "blkuc3" "960,895.56" "1" "1" "180")
(command "_insert" "blkuc3" "960,896.3" "1" "1" "0")
(command "_insert" "blkuc3" "960,895.93" "1" "1" "180")
(command "_insert" "blkuc3" "960,896.67" "1" "1" "0")
(command "_insert" "blkuc3" "960,896.3" "1" "1" "180")
(command "_insert" "blkuc3" "960,897.04" "1" "1" "0")
(command "_insert" "blkuc3" "960,896.67" "1" "1" "180")
(command "_insert" "blkuc3" "960,897.41" "1" "1" "0")
(command "_insert" "blkuc3" "960,897.04" "1" "1" "180")
(command "_insert" "blkuc3" "960,897.78" "1" "1" "0")
(command "_insert" "blkuc3" "960,897.41" "1" "1" "180")
(command "_insert" "blkuc3" "960,898.15" "1" "1" "0")
(command "_insert" "blkuc3" "960,897.78" "1" "1" "180")
(command "_insert" "blkuc3" "960,898.52" "1" "1" "0")
(command "_insert" "blkuc3" "960,898.15" "1" "1" "180")
(command "_insert" "blkuc3" "960,898.89" "1" "1" "0")
(command "_insert" "blkuc3" "960,898.52" "1" "1" "180")
(command "_insert" "blkuc3" "960,899.26" "1" "1" "0")
(command "_insert" "blkuc3" "960,898.89" "1" "1" "180")
(command "_insert" "blkuc3" "960,899.63" "1" "1" "0")
(command "_insert" "blkuc3" "960,899.26" "1" "1" "180")
(command "_insert" "blkuc3" "960,900" "1" "1" "0")
(command "_insert" "blkuc3" "960,899.63" "1" "1" "180")
(command "_insert" "blkuc3" "960,900.37" "1" "1" "0")
(command "_insert" "blkuc3" "960,900" "1" "1" "180")
(command "_insert" "blkuc3" "960,900.74" "1" "1" "0")
(command "_insert" "blkuc3" "960,900.37" "1" "1" "180")
(command "_insert" "blkuc3" "960,901.11" "1" "1" "0")
(command "_insert" "blkuc3" "960,900.74" "1" "1" "180")
(command "_insert" "blkuc3" "960,901.48" "1" "1" "0")
(command "_insert" "blkuc3" "960,901.11" "1" "1" "180")
(command "_insert" "blkuc3" "960,901.85" "1" "1" "0")
(command "_insert" "blkuc3" "960,901.48" "1" "1" "180")
(command "_insert" "blkuc3" "960,902.22" "1" "1" "0")
(command "_insert" "blkuc3" "960,901.85" "1" "1" "180")
(command "_insert" "blkuc3" "960,902.59" "1" "1" "0")
(command "_insert" "blkuc3" "960,902.22" "1" "1" "180")
(command "_insert" "blkuc3" "960,902.96" "1" "1" "0")
(command "_insert" "blkuc3" "960,902.59" "1" "1" "180")
(command "_insert" "blkuc3" "960,903.33" "1" "1" "0")
(command "_insert" "blkuc3" "960,902.96" "1" "1" "180")
(command "_insert" "blkuc3" "960,903.7" "1" "1" "0")
(command "_insert" "blkuc3" "960,903.33" "1" "1" "180")
(command "_insert" "blkuc3" "960,904.07" "1" "1" "0")
(command "_insert" "blkuc3" "960,903.7" "1" "1" "180")
(command "_insert" "blkuc3" "960,904.44" "1" "1" "0")
(command "_insert" "blkuc3" "960,904.07" "1" "1" "180")
(command "_insert" "blkuc3" "960,904.81" "1" "1" "0")
(command "_insert" "blkuc3" "960,904.44" "1" "1" "180")
(command "_insert" "blkuc3" "960,905.18" "1" "1" "0")
(command "_insert" "blkuc3" "960,904.81" "1" "1" "180")
(command "_insert" "blkuc3" "960,905.55" "1" "1" "0")
(command "_insert" "blkuc3" "960,905.18" "1" "1" "180")
(command "_insert" "blkuc3" "960,905.92" "1" "1" "0")
(command "_insert" "blkuc3" "960,905.55" "1" "1" "180")
(command "_insert" "blkuc3" "960,906.29" "1" "1" "0")
(command "_insert" "blkuc3" "960,905.92" "1" "1" "180")
(command "_insert" "blkuc3" "960,906.66" "1" "1" "0")
(command "_insert" "blkuc3" "960,906.29" "1" "1" "180")
(command "_insert" "blkuc3" "960,907.03" "1" "1" "0")
(command "_insert" "blkuc3" "960,906.66" "1" "1" "180")
(command "_insert" "blkuc3" "960,907.4" "1" "1" "0")
(command "_insert" "blkuc3" "960,907.03" "1" "1" "180")
(command "_insert" "blkuc3" "960,907.77" "1" "1" "0")
(command "_insert" "blkuc3" "960,907.4" "1" "1" "180")
(command "_insert" "blkuc3" "960,908.14" "1" "1" "0")
(command "_insert" "blkuc3" "960,907.77" "1" "1" "180")
(command "_insert" "blkuc3" "960,908.51" "1" "1" "0")
(command "_insert" "blkuc3" "960,908.14" "1" "1" "180")
(command "_insert" "blkuc3" "960,908.88" "1" "1" "0")
(command "_insert" "blkuc3" "960,908.51" "1" "1" "180")
(command "_insert" "blkuc3" "960,909.25" "1" "1" "0")
(command "_insert" "blkuc3" "960,908.88" "1" "1" "180")
(command "_insert" "blkuc3" "960,909.62" "1" "1" "0")
(command "_insert" "blkuc3" "960,909.25" "1" "1" "180")
(command "_insert" "blkuc3" "960,909.99" "1" "1" "0")
(command "_insert" "blkuc3" "960,909.62" "1" "1" "180")
(command "_insert" "blkuc3" "960,910.36" "1" "1" "0")
(command "_insert" "blkuc3" "960,909.99" "1" "1" "180")
(command "_insert" "blkuc3" "960,910.73" "1" "1" "0")
(command "_insert" "blkuc3" "960,910.36" "1" "1" "180")
(command "_insert" "blkuc3" "960,911.1" "1" "1" "0")
(command "_insert" "blkuc3" "960,910.73" "1" "1" "180")
(command "_insert" "blkuc3" "960,911.47" "1" "1" "0")
(command "_insert" "blkuc3" "960,911.1" "1" "1" "180")
(command "_insert" "blkuc3" "960,911.84" "1" "1" "0")
(command "_insert" "blkuc3" "960,911.47" "1" "1" "180")
(command "_insert" "blkuc3" "960,912.21" "1" "1" "0")
(command "_insert" "blkuc3" "960,911.84" "1" "1" "180")
(command "_insert" "blkuc3" "960,912.58" "1" "1" "0")
(command "_insert" "blkuc3" "960,912.21" "1" "1" "180")
(command "_insert" "blkuc3" "960,912.95" "1" "1" "0")
(command "_insert" "blkuc3" "960,912.58" "1" "1" "180")
(command "_insert" "blkuc3" "960,913.32" "1" "1" "0")
(command "_insert" "blkuc3" "960,912.95" "1" "1" "180")
(command "_insert" "blkuc3" "960,913.69" "1" "1" "0")
(command "_insert" "blkuc3" "960,913.32" "1" "1" "180")
(command "_insert" "blkuc3" "960,914.06" "1" "1" "0")
(command "_insert" "blkuc3" "960,913.69" "1" "1" "180")
(command "_insert" "blkuc3" "960,914.43" "1" "1" "0")
(command "_insert" "blkuc3" "960,914.06" "1" "1" "180")
(command "_insert" "blkuc3" "960,914.8" "1" "1" "0")
(command "_insert" "blkuc3" "960,914.43" "1" "1" "180")
(command "_insert" "blkuc3" "960,915.17" "1" "1" "0")
(command "_insert" "blkuc3" "960,914.8" "1" "1" "180")
(command "_insert" "blkuc3" "960,915.54" "1" "1" "0")
(command "_insert" "blkuc3" "960,915.17" "1" "1" "180")
(command "_insert" "blkuc3" "960,915.91" "1" "1" "0")
(command "_insert" "blkuc3" "960,915.54" "1" "1" "180")
(command "_insert" "blkuc3" "960,916.28" "1" "1" "0")
(command "_insert" "blkuc3" "960,915.91" "1" "1" "180")
(command "_insert" "blkuc3" "960,916.65" "1" "1" "0")
(command "_insert" "blkuc3" "960,916.28" "1" "1" "180")
(command "_insert" "blkuc3" "960,917.02" "1" "1" "0")
(command "_insert" "blkuc3" "960,916.65" "1" "1" "180")
(command "_insert" "blkuc3" "960,917.39" "1" "1" "0")
(command "_insert" "blkuc3" "960,917.02" "1" "1" "180")
(command "_insert" "blkuc3" "960,917.76" "1" "1" "0")
(command "_insert" "blkuc3" "960,917.39" "1" "1" "180")
(command "_insert" "blkuc3" "960,918.13" "1" "1" "0")
(command "_insert" "blkuc3" "960,917.76" "1" "1" "180")
(command "_insert" "blkuc3" "960,918.5" "1" "1" "0")
(command "_insert" "blkuc3" "960,918.13" "1" "1" "180")
(command "_insert" "blkuc3" "960,918.87" "1" "1" "0")
(command "_insert" "blkuc3" "960,918.5" "1" "1" "180")
(command "_insert" "blkuc3" "960,919.24" "1" "1" "0")
(command "_insert" "blkuc3" "960,918.87" "1" "1" "180")
(command "_insert" "blkuc3" "960,919.61" "1" "1" "0")
(command "_insert" "blkuc3" "960,919.24" "1" "1" "180")
(command "_insert" "blkuc3" "960,919.98" "1" "1" "0")
(command "_insert" "blkuc3" "960,919.61" "1" "1" "180")
(command "_insert" "blkuc3" "960,920.35" "1" "1" "0")
(command "_insert" "blkuc3" "960,919.98" "1" "1" "180")
(command "_insert" "blkuc3" "960,920.72" "1" "1" "0")
(command "_insert" "blkuc3" "960,920.35" "1" "1" "180")
(command "_insert" "blkuc3" "960,921.09" "1" "1" "0")
(command "_insert" "blkuc3" "960,920.72" "1" "1" "180")
(command "_insert" "blkuc3" "960,921.46" "1" "1" "0")
(command "_insert" "blkuc3" "960,921.09" "1" "1" "180")
(command "_insert" "blkuc3" "960,921.83" "1" "1" "0")
(command "_insert" "blkuc3" "960,921.46" "1" "1" "180")
(command "_insert" "blkuc3" "960,922.2" "1" "1" "0")
(command "_insert" "blkuc3" "960,921.83" "1" "1" "180")
(command "_insert" "blkuc3" "960,922.57" "1" "1" "0")
(command "_insert" "blkuc3" "960,922.2" "1" "1" "180")
(command "_insert" "blkuc3" "960,922.94" "1" "1" "0")
(command "_insert" "blkuc3" "960,922.57" "1" "1" "180")
(command "_insert" "blkuc3" "960,923.31" "1" "1" "0")
(command "_insert" "blkuc3" "960,922.94" "1" "1" "180")
(command "_insert" "blkuc3" "960,923.68" "1" "1" "0")
(command "_insert" "blkuc3" "960,923.31" "1" "1" "180")
(command "_insert" "blkuc3" "960,924.05" "1" "1" "0")
(command "_insert" "blkuc3" "960,923.68" "1" "1" "180")
(command "_insert" "blkuc3" "960,924.42" "1" "1" "0")
(command "_insert" "blkuc3" "960,924.05" "1" "1" "180")
(command "_insert" "blkuc3" "960,924.79" "1" "1" "0")
(command "_insert" "blkuc3" "960,924.42" "1" "1" "180")
(command "_insert" "blkuc3" "960,925.16" "1" "1" "0")
(command "_insert" "blkuc3" "960,924.79" "1" "1" "180")
(command "_insert" "blkuc3" "960,925.53" "1" "1" "0")
(command "_insert" "blkuc3" "960,925.16" "1" "1" "180")
(command "_insert" "blkuc3" "960,925.9" "1" "1" "0")
(command "_insert" "blkuc3" "960,925.53" "1" "1" "180")
(command "_insert" "blkuc3" "960,926.27" "1" "1" "0")
(command "_insert" "blkuc3" "960,925.9" "1" "1" "180")
(command "_insert" "blkuc3" "960,926.64" "1" "1" "0")
(command "_insert" "blkuc3" "960,926.27" "1" "1" "180")
(command "_insert" "blkuc3" "960,927.01" "1" "1" "0")
(command "_insert" "blkuc3" "960,926.64" "1" "1" "180")
(command "_insert" "blkuc3" "960,927.38" "1" "1" "0")
(command "_insert" "blkuc3" "960,927.01" "1" "1" "180")
(command "_insert" "blkuc3" "960,927.75" "1" "1" "0")
(command "_insert" "blkuc3" "960,927.38" "1" "1" "180")
(command "_layer" "set" "phccover" "")
(command "_rectangle" "958.876,933.3" "961.124,866.7")
(command "_layer" "set" "nitride" "")
(setq phc3 currobj)
(command "_layer" "set" "cover" "")
(command "_rectangle" "958.876,836.7" "961.124,963.3")
(command "_layer" "set" "nitride" "")
(command "_layer" "set" "text" "")
(command "_circle" "957.926,846.7" "0.075")
(command "_circle" "957.551,846.7" "0.15")
(command "_circle" "957.176,846.7" "0.075")
(command "_circle" "956.801,846.7" "0.15")
(command "_circle" "957.926,848.7" "0.075")
(command "_circle" "957.551,848.7" "0.075")
(command "_circle" "957.176,848.7" "0.15")
(command "_circle" "956.801,848.7" "0.15")
(command "_circle" "957.926,850.7" "0.075")
(command "_circle" "957.551,850.7" "0.15")
(command "_circle" "957.176,850.7" "0.15")
(command "_circle" "956.801,850.7" "0.15")
(command "_circle" "957.926,852.7" "0.075")
(command "_circle" "957.551,852.7" "0.075")
(command "_circle" "957.176,852.7" "0.075")
(command "_circle" "956.801,852.7" "0.075")
(command "_circle" "956.426,852.7" "0.15")
(command "_circle" "957.926,854.7" "0.075")
(command "_circle" "957.551,854.7" "0.15")
(command "_circle" "957.176,854.7" "0.075")
(command "_circle" "956.801,854.7" "0.075")
(command "_circle" "956.426,854.7" "0.15")
(command "_circle" "957.926,856.7" "0.075")
(command "_circle" "957.551,856.7" "0.075")
(command "_circle" "957.176,856.7" "0.15")
(command "_circle" "956.801,856.7" "0.075")
(command "_circle" "956.426,856.7" "0.15")
(command "_circle" "957.926,858.7" "0.075")
(command "_circle" "957.551,858.7" "0.15")
(command "_circle" "957.176,858.7" "0.15")
(command "_circle" "956.801,858.7" "0.075")
(command "_circle" "956.426,858.7" "0.15")
(command "_circle" "957.926,860.7" "0.075")
(command "_circle" "957.551,860.7" "0.075")
(command "_circle" "957.176,860.7" "0.075")
(command "_circle" "956.801,860.7" "0.15")
(command "_circle" "956.426,860.7" "0.15")
(command "_circle" "957.926,862.7" "0.075")
(command "_circle" "957.551,862.7" "0.15")
(command "_circle" "957.176,862.7" "0.075")
(command "_circle" "956.801,862.7" "0.15")
(command "_circle" "956.426,862.7" "0.15")
(command "_circle" "957.926,864.7" "0.075")
(command "_circle" "957.551,864.7" "0.075")
(command "_circle" "957.176,864.7" "0.15")
(command "_circle" "956.801,864.7" "0.15")
(command "_circle" "956.426,864.7" "0.15")
(command "_circle" "957.926,866.7" "0.075")
(command "_circle" "957.551,866.7" "0.15")
(command "_circle" "957.176,866.7" "0.15")
(command "_circle" "956.801,866.7" "0.15")
(command "_circle" "956.426,866.7" "0.15")
(command "_circle" "957.926,868.7" "0.075")
(command "_circle" "957.551,868.7" "0.075")
(command "_circle" "957.176,868.7" "0.075")
(command "_circle" "956.801,868.7" "0.075")
(command "_circle" "956.426,868.7" "0.075")
(command "_circle" "956.051,868.7" "0.15")
(command "_circle" "957.926,870.7" "0.075")
(command "_circle" "957.551,870.7" "0.15")
(command "_circle" "957.176,870.7" "0.075")
(command "_circle" "956.801,870.7" "0.075")
(command "_circle" "956.426,870.7" "0.075")
(command "_circle" "956.051,870.7" "0.15")
(command "_circle" "957.926,872.7" "0.075")
(command "_circle" "957.551,872.7" "0.075")
(command "_circle" "957.176,872.7" "0.15")
(command "_circle" "956.801,872.7" "0.075")
(command "_circle" "956.426,872.7" "0.075")
(command "_circle" "956.051,872.7" "0.15")
(command "_circle" "957.926,874.7" "0.075")
(command "_circle" "957.551,874.7" "0.15")
(command "_circle" "957.176,874.7" "0.15")
(command "_circle" "956.801,874.7" "0.075")
(command "_circle" "956.426,874.7" "0.075")
(command "_circle" "956.051,874.7" "0.15")
(command "_circle" "957.926,876.7" "0.075")
(command "_circle" "957.551,876.7" "0.075")
(command "_circle" "957.176,876.7" "0.075")
(command "_circle" "956.801,876.7" "0.15")
(command "_circle" "956.426,876.7" "0.075")
(command "_circle" "956.051,876.7" "0.15")
(command "_circle" "957.926,878.7" "0.075")
(command "_circle" "957.551,878.7" "0.15")
(command "_circle" "957.176,878.7" "0.075")
(command "_circle" "956.801,878.7" "0.15")
(command "_circle" "956.426,878.7" "0.075")
(command "_circle" "956.051,878.7" "0.15")
(command "_circle" "957.926,880.7" "0.075")
(command "_circle" "957.551,880.7" "0.075")
(command "_circle" "957.176,880.7" "0.15")
(command "_circle" "956.801,880.7" "0.15")
(command "_circle" "956.426,880.7" "0.075")
(command "_circle" "956.051,880.7" "0.15")
(command "_circle" "957.926,882.7" "0.075")
(command "_circle" "957.551,882.7" "0.15")
(command "_circle" "957.176,882.7" "0.15")
(command "_circle" "956.801,882.7" "0.15")
(command "_circle" "956.426,882.7" "0.075")
(command "_circle" "956.051,882.7" "0.15")
(command "_circle" "957.926,884.7" "0.075")
(command "_circle" "957.551,884.7" "0.075")
(command "_circle" "957.176,884.7" "0.075")
(command "_circle" "956.801,884.7" "0.075")
(command "_circle" "956.426,884.7" "0.15")
(command "_circle" "956.051,884.7" "0.15")
(command "_circle" "957.926,886.7" "0.075")
(command "_circle" "957.551,886.7" "0.15")
(command "_circle" "957.176,886.7" "0.075")
(command "_circle" "956.801,886.7" "0.075")
(command "_circle" "956.426,886.7" "0.15")
(command "_circle" "956.051,886.7" "0.15")
(command "_circle" "957.926,888.7" "0.075")
(command "_circle" "957.551,888.7" "0.075")
(command "_circle" "957.176,888.7" "0.15")
(command "_circle" "956.801,888.7" "0.075")
(command "_circle" "956.426,888.7" "0.15")
(command "_circle" "956.051,888.7" "0.15")
(command "_circle" "957.926,890.7" "0.075")
(command "_circle" "957.551,890.7" "0.15")
(command "_circle" "957.176,890.7" "0.15")
(command "_circle" "956.801,890.7" "0.075")
(command "_circle" "956.426,890.7" "0.15")
(command "_circle" "956.051,890.7" "0.15")
(command "_circle" "957.926,892.7" "0.075")
(command "_circle" "957.551,892.7" "0.075")
(command "_circle" "957.176,892.7" "0.075")
(command "_circle" "956.801,892.7" "0.15")
(command "_circle" "956.426,892.7" "0.15")
(command "_circle" "956.051,892.7" "0.15")
(command "_circle" "957.926,894.7" "0.075")
(command "_circle" "957.551,894.7" "0.15")
(command "_circle" "957.176,894.7" "0.075")
(command "_circle" "956.801,894.7" "0.15")
(command "_circle" "956.426,894.7" "0.15")
(command "_circle" "956.051,894.7" "0.15")
(command "_circle" "957.926,896.7" "0.075")
(command "_circle" "957.551,896.7" "0.075")
(command "_circle" "957.176,896.7" "0.15")
(command "_circle" "956.801,896.7" "0.15")
(command "_circle" "956.426,896.7" "0.15")
(command "_circle" "956.051,896.7" "0.15")
(command "_circle" "957.926,898.7" "0.075")
(command "_circle" "957.551,898.7" "0.15")
(command "_circle" "957.176,898.7" "0.15")
(command "_circle" "956.801,898.7" "0.15")
(command "_circle" "956.426,898.7" "0.15")
(command "_circle" "956.051,898.7" "0.15")
(command "_circle" "957.926,900.7" "0.075")
(command "_circle" "957.551,900.7" "0.075")
(command "_circle" "957.176,900.7" "0.075")
(command "_circle" "956.801,900.7" "0.075")
(command "_circle" "956.426,900.7" "0.075")
(command "_circle" "956.051,900.7" "0.075")
(command "_circle" "955.676,900.7" "0.15")
(command "_circle" "957.926,902.7" "0.075")
(command "_circle" "957.551,902.7" "0.15")
(command "_circle" "957.176,902.7" "0.075")
(command "_circle" "956.801,902.7" "0.075")
(command "_circle" "956.426,902.7" "0.075")
(command "_circle" "956.051,902.7" "0.075")
(command "_circle" "955.676,902.7" "0.15")
(command "_circle" "957.926,904.7" "0.075")
(command "_circle" "957.551,904.7" "0.075")
(command "_circle" "957.176,904.7" "0.15")
(command "_circle" "956.801,904.7" "0.075")
(command "_circle" "956.426,904.7" "0.075")
(command "_circle" "956.051,904.7" "0.075")
(command "_circle" "955.676,904.7" "0.15")
(command "_circle" "957.926,906.7" "0.075")
(command "_circle" "957.551,906.7" "0.15")
(command "_circle" "957.176,906.7" "0.15")
(command "_circle" "956.801,906.7" "0.075")
(command "_circle" "956.426,906.7" "0.075")
(command "_circle" "956.051,906.7" "0.075")
(command "_circle" "955.676,906.7" "0.15")
(command "_circle" "957.926,908.7" "0.075")
(command "_circle" "957.551,908.7" "0.075")
(command "_circle" "957.176,908.7" "0.075")
(command "_circle" "956.801,908.7" "0.15")
(command "_circle" "956.426,908.7" "0.075")
(command "_circle" "956.051,908.7" "0.075")
(command "_circle" "955.676,908.7" "0.15")
(command "_circle" "957.926,910.7" "0.075")
(command "_circle" "957.551,910.7" "0.15")
(command "_circle" "957.176,910.7" "0.075")
(command "_circle" "956.801,910.7" "0.15")
(command "_circle" "956.426,910.7" "0.075")
(command "_circle" "956.051,910.7" "0.075")
(command "_circle" "955.676,910.7" "0.15")
(command "_circle" "957.926,912.7" "0.075")
(command "_circle" "957.551,912.7" "0.075")
(command "_circle" "957.176,912.7" "0.15")
(command "_circle" "956.801,912.7" "0.15")
(command "_circle" "956.426,912.7" "0.075")
(command "_circle" "956.051,912.7" "0.075")
(command "_circle" "955.676,912.7" "0.15")
(command "_circle" "957.926,914.7" "0.075")
(command "_circle" "957.551,914.7" "0.15")
(command "_circle" "957.176,914.7" "0.15")
(command "_circle" "956.801,914.7" "0.15")
(command "_circle" "956.426,914.7" "0.075")
(command "_circle" "956.051,914.7" "0.075")
(command "_circle" "955.676,914.7" "0.15")
(command "_circle" "957.926,916.7" "0.075")
(command "_circle" "957.551,916.7" "0.075")
(command "_circle" "957.176,916.7" "0.075")
(command "_circle" "956.801,916.7" "0.075")
(command "_circle" "956.426,916.7" "0.15")
(command "_circle" "956.051,916.7" "0.075")
(command "_circle" "955.676,916.7" "0.15")
(command "_circle" "957.926,918.7" "0.075")
(command "_circle" "957.551,918.7" "0.15")
(command "_circle" "957.176,918.7" "0.075")
(command "_circle" "956.801,918.7" "0.075")
(command "_circle" "956.426,918.7" "0.15")
(command "_circle" "956.051,918.7" "0.075")
(command "_circle" "955.676,918.7" "0.15")
(command "_circle" "957.926,920.7" "0.075")
(command "_circle" "957.551,920.7" "0.075")
(command "_circle" "957.176,920.7" "0.15")
(command "_circle" "956.801,920.7" "0.075")
(command "_circle" "956.426,920.7" "0.15")
(command "_circle" "956.051,920.7" "0.075")
(command "_circle" "955.676,920.7" "0.15")
(command "_circle" "957.926,922.7" "0.075")
(command "_circle" "957.551,922.7" "0.15")
(command "_circle" "957.176,922.7" "0.15")
(command "_circle" "956.801,922.7" "0.075")
(command "_circle" "956.426,922.7" "0.15")
(command "_circle" "956.051,922.7" "0.075")
(command "_circle" "955.676,922.7" "0.15")
(command "_circle" "957.926,924.7" "0.075")
(command "_circle" "957.551,924.7" "0.075")
(command "_circle" "957.176,924.7" "0.075")
(command "_circle" "956.801,924.7" "0.15")
(command "_circle" "956.426,924.7" "0.15")
(command "_circle" "956.051,924.7" "0.075")
(command "_circle" "955.676,924.7" "0.15")
(command "_circle" "957.926,926.7" "0.075")
(command "_circle" "957.551,926.7" "0.15")
(command "_circle" "957.176,926.7" "0.075")
(command "_circle" "956.801,926.7" "0.15")
(command "_circle" "956.426,926.7" "0.15")
(command "_circle" "956.051,926.7" "0.075")
(command "_circle" "955.676,926.7" "0.15")
(command "_circle" "957.926,928.7" "0.075")
(command "_circle" "957.551,928.7" "0.075")
(command "_circle" "957.176,928.7" "0.15")
(command "_circle" "956.801,928.7" "0.15")
(command "_circle" "956.426,928.7" "0.15")
(command "_circle" "956.051,928.7" "0.075")
(command "_circle" "955.676,928.7" "0.15")
(command "_circle" "957.926,930.7" "0.075")
(command "_circle" "957.551,930.7" "0.15")
(command "_circle" "957.176,930.7" "0.15")
(command "_circle" "956.801,930.7" "0.15")
(command "_circle" "956.426,930.7" "0.15")
(command "_circle" "956.051,930.7" "0.075")
(command "_circle" "955.676,930.7" "0.15")
(command "_circle" "957.926,932.7" "0.075")
(command "_circle" "957.551,932.7" "0.075")
(command "_circle" "957.176,932.7" "0.075")
(command "_circle" "956.801,932.7" "0.075")
(command "_circle" "956.426,932.7" "0.075")
(command "_circle" "956.051,932.7" "0.15")
(command "_circle" "955.676,932.7" "0.15")
(command "_circle" "957.926,934.7" "0.075")
(command "_circle" "957.551,934.7" "0.15")
(command "_circle" "957.176,934.7" "0.075")
(command "_circle" "956.801,934.7" "0.075")
(command "_circle" "956.426,934.7" "0.075")
(command "_circle" "956.051,934.7" "0.15")
(command "_circle" "955.676,934.7" "0.15")
(command "_circle" "957.926,936.7" "0.075")
(command "_circle" "957.551,936.7" "0.075")
(command "_circle" "957.176,936.7" "0.15")
(command "_circle" "956.801,936.7" "0.075")
(command "_circle" "956.426,936.7" "0.075")
(command "_circle" "956.051,936.7" "0.15")
(command "_circle" "955.676,936.7" "0.15")
(command "_circle" "957.926,938.7" "0.075")
(command "_circle" "957.551,938.7" "0.15")
(command "_circle" "957.176,938.7" "0.15")
(command "_circle" "956.801,938.7" "0.075")
(command "_circle" "956.426,938.7" "0.075")
(command "_circle" "956.051,938.7" "0.15")
(command "_circle" "955.676,938.7" "0.15")
(command "_circle" "957.926,940.7" "0.075")
(command "_circle" "957.551,940.7" "0.075")
(command "_circle" "957.176,940.7" "0.075")
(command "_circle" "956.801,940.7" "0.15")
(command "_circle" "956.426,940.7" "0.075")
(command "_circle" "956.051,940.7" "0.15")
(command "_circle" "955.676,940.7" "0.15")
(command "_circle" "957.926,942.7" "0.075")
(command "_circle" "957.551,942.7" "0.15")
(command "_circle" "957.176,942.7" "0.075")
(command "_circle" "956.801,942.7" "0.15")
(command "_circle" "956.426,942.7" "0.075")
(command "_circle" "956.051,942.7" "0.15")
(command "_circle" "955.676,942.7" "0.15")
(command "_circle" "957.926,944.7" "0.075")
(command "_circle" "957.551,944.7" "0.075")
(command "_circle" "957.176,944.7" "0.15")
(command "_circle" "956.801,944.7" "0.15")
(command "_circle" "956.426,944.7" "0.075")
(command "_circle" "956.051,944.7" "0.15")
(command "_circle" "955.676,944.7" "0.15")
(command "_circle" "957.926,946.7" "0.075")
(command "_circle" "957.551,946.7" "0.15")
(command "_circle" "957.176,946.7" "0.15")
(command "_circle" "956.801,946.7" "0.15")
(command "_circle" "956.426,946.7" "0.075")
(command "_circle" "956.051,946.7" "0.15")
(command "_circle" "955.676,946.7" "0.15")
(command "_circle" "957.926,948.7" "0.075")
(command "_circle" "957.551,948.7" "0.075")
(command "_circle" "957.176,948.7" "0.075")
(command "_circle" "956.801,948.7" "0.075")
(command "_circle" "956.426,948.7" "0.15")
(command "_circle" "956.051,948.7" "0.15")
(command "_circle" "955.676,948.7" "0.15")
(command "_circle" "957.926,950.7" "0.075")
(command "_circle" "957.551,950.7" "0.15")
(command "_circle" "957.176,950.7" "0.075")
(command "_circle" "956.801,950.7" "0.075")
(command "_circle" "956.426,950.7" "0.15")
(command "_circle" "956.051,950.7" "0.15")
(command "_circle" "955.676,950.7" "0.15")
(command "_circle" "957.926,952.7" "0.075")
(command "_circle" "957.551,952.7" "0.075")
(command "_circle" "957.176,952.7" "0.15")
(command "_circle" "956.801,952.7" "0.075")
(command "_circle" "956.426,952.7" "0.15")
(command "_circle" "956.051,952.7" "0.15")
(command "_circle" "955.676,952.7" "0.15")
(command "_circle" "957.926,954.7" "0.075")
(command "_circle" "957.551,954.7" "0.15")
(command "_circle" "957.176,954.7" "0.15")
(command "_circle" "956.801,954.7" "0.075")
(command "_circle" "956.426,954.7" "0.15")
(command "_circle" "956.051,954.7" "0.15")
(command "_circle" "955.676,954.7" "0.15")
(command "_circle" "957.926,956.7" "0.075")
(command "_circle" "957.551,956.7" "0.075")
(command "_circle" "957.176,956.7" "0.075")
(command "_circle" "956.801,956.7" "0.15")
(command "_circle" "956.426,956.7" "0.15")
(command "_circle" "956.051,956.7" "0.15")
(command "_circle" "955.676,956.7" "0.15")
(command "_circle" "957.926,958.7" "0.075")
(command "_circle" "957.551,958.7" "0.15")
(command "_circle" "957.176,958.7" "0.075")
(command "_circle" "956.801,958.7" "0.15")
(command "_circle" "956.426,958.7" "0.15")
(command "_circle" "956.051,958.7" "0.15")
(command "_circle" "955.676,958.7" "0.15")
(command "_circle" "957.926,960.7" "0.075")
(command "_circle" "957.551,960.7" "0.075")
(command "_circle" "957.176,960.7" "0.15")
(command "_circle" "956.801,960.7" "0.15")
(command "_circle" "956.426,960.7" "0.15")
(command "_circle" "956.051,960.7" "0.15")
(command "_circle" "955.676,960.7" "0.15")
(command "_circle" "957.926,962.7" "0.075")
(command "_circle" "957.551,962.7" "0.15")
(command "_circle" "957.176,962.7" "0.15")
(command "_circle" "956.801,962.7" "0.15")
(command "_circle" "956.426,962.7" "0.15")
(command "_circle" "956.051,962.7" "0.15")
(command "_circle" "955.676,962.7" "0.15")
(command "_layer" "set" "nitride" "")
(command "_layer" "set" "text" "")
(command-s "_text" "946.876,963.3" "2" "-90" "a = 370 nm" )
(sssetfirst nil (ssget "_L"))
(if (not (numberp (vl-string-search "Mac" (getvar "platform")))) (c:txtexp))
(command "_layer" "set" "nitride" "")
(command "_layer" "set" "text" "")
(command-s "_text" "943.876,963.3" "2" "-90" "gap = 270 nm" )
(sssetfirst nil (ssget "_L"))
(if (not (numberp (vl-string-search "Mac" (getvar "platform")))) (c:txtexp))
(command "_layer" "set" "nitride" "")
(command "_layer" "set" "text" "")
(command-s "_text" "940.876,963.3" "2" "-90" "amplitude = 135 nm" )
(sssetfirst nil (ssget "_L"))
(if (not (numberp (vl-string-search "Mac" (getvar "platform")))) (c:txtexp))
(command "_layer" "set" "nitride" "")
(command "_layer" "set" "text" "")
(command-s "_text" "937.876,963.3" "2" "-90" "start width = 280 nm" )
(sssetfirst nil (ssget "_L"))
(if (not (numberp (vl-string-search "Mac" (getvar "platform")))) (c:txtexp))
(command "_layer" "set" "nitride" "")
(command "_layer" "set" "text" "")
(command-s "_text" "934.876,963.3" "2" "-90" "width = 292 nm" )
(sssetfirst nil (ssget "_L"))
(if (not (numberp (vl-string-search "Mac" (getvar "platform")))) (c:txtexp))
(command "_layer" "set" "nitride" "")
(command "_layer" "set" "text" "")
(command-s "_text" "931.876,963.3" "2" "-90" "taper: 15" )
(sssetfirst nil (ssget "_L"))
(if (not (numberp (vl-string-search "Mac" (getvar "platform")))) (c:txtexp))
(command "_layer" "set" "nitride" "")
(command "_layer" "set" "text" "")
(command-s "_text" "928.876,963.3" "2" "-90" "nominal: 150" )
(sssetfirst nil (ssget "_L"))
(if (not (numberp (vl-string-search "Mac" (getvar "platform")))) (c:txtexp))
(command "_layer" "set" "nitride" "")
(command "_layer" "set" "indicators" "")
(setq coords (list 
(list 880.415 940) 
(list 880.415 920) 
(list 860.415 900) 
(list 880.415 880) 
(list 880.415 860) 
(list 880.415 900) 
(list 880.415 887.0711) 
(list 867.4861 900) 
(list 880.415 912.9289) 
(list 880.415 900)))
(apply 'command (append '("pline") coords '("c")))
(command "._fillet" "radius" "1" "._fillet" "P" (entlast))
(setq coords (list 
(list 1039.585 940) 
(list 1039.585 920) 
(list 1059.585 900) 
(list 1039.585 880) 
(list 1039.585 860) 
(list 1039.585 900) 
(list 1039.585 887.0711) 
(list 1052.5139 900) 
(list 1039.585 912.9289) 
(list 1039.585 900)))
(apply 'command (append '("pline") coords '("c")))
(command "._fillet" "radius" "1" "._fillet" "P" (entlast))
(command "_layer" "set" "holes" "")
(command "_circle" "878.0629,914.1124" "0.5")
(command "_circle" "875.7109,911.7603" "0.5")
(command "_circle" "873.3588,909.4083" "0.5")
(command "_circle" "871.0067,907.0562" "0.5")
(command "_circle" "868.6547,904.7041" "0.5")
(command "_circle" "866.3026,902.3521" "0.5")
(command "_circle" "863.9505,900" "0.5")
(command "_circle" "866.3026,897.6479" "0.5")
(command "_circle" "868.6547,895.2959" "0.5")
(command "_circle" "871.0067,892.9438" "0.5")
(command "_circle" "873.3588,890.5917" "0.5")
(command "_circle" "875.7109,888.2397" "0.5")
(command "_circle" "878.0629,885.8876" "0.5")
(command "_circle" "1041.9371,914.1124" "0.5")
(command "_circle" "1044.2891,911.7603" "0.5")
(command "_circle" "1046.6412,909.4083" "0.5")
(command "_circle" "1048.9933,907.0562" "0.5")
(command "_circle" "1051.3453,904.7041" "0.5")
(command "_circle" "1053.6974,902.3521" "0.5")
(command "_circle" "1056.0495,900" "0.5")
(command "_circle" "1053.6974,897.6479" "0.5")
(command "_circle" "1051.3453,895.2959" "0.5")
(command "_circle" "1048.9933,892.9438" "0.5")
(command "_circle" "1046.6412,890.5917" "0.5")
(command "_circle" "1044.2891,888.2397" "0.5")
(command "_circle" "1041.9371,885.8876" "0.5")
(command "_layer" "set" "nitride" "")
(command "_block" "blkcoupler3" "960,900" coupler3 "")
(command "_insert" "blkcoupler3" "960,900" "1" "1" "0")
(command "_insert" "blkcoupler3" "960,900" "1" "1" "180")
(command "_block" "blksinglenanobeam3" "960,900" singlenanobeam3 "")
(command "_insert" "blksinglenanobeam3" "960,900" "1" "1" "0")
(command "_insert" "blksinglenanobeam3" "960,900" "1" "1" "180")
(command "_block" "blkanglednodearray3" "960,900" anglednodearray3 "")
(command "_insert" "blkanglednodearray3" "960,900" "1" "1" "0")
(command "_insert" "blkanglednodearray3" "960,900" "1" "1" "180")
(command "_block" "blkcooledsinglenanobeam3" "960,900" cooledsinglenanobeam3 "")
(command "_insert" "blkcooledsinglenanobeam3" "960,900" "1" "1" "0")
(command "_insert" "blkcooledsinglenanobeam3" "960,900" "1" "1" "180")
(command "_block" "blkyjunction3" "960,900" yjunction3 "")
(command "_insert" "blkyjunction3" "960,900" "1" "1" "0")
(command "_insert" "blkyjunction3" "960,900" "1" "1" "180")
; DRAWING BULGING VEE GROOVE
(command "_layer" "set" "vgroove" "")
(setq coords (list 
(list 885.415 -605) 
(list 885.415 0) 
(list 885.415 0) 
(list 885.415 1800) 
(list 885.415 1800) 
(list 885.415 2405) 
(list 1034.585 2405) 
(list 1034.585 1800) 
(list 1034.585 1800) 
(list 1034.585 0) 
(list 1034.585 0) 
(list 1034.585 -605)))
(apply 'command (append '("pline") coords '("c")))
(command "._fillet" "radius" "0" "._fillet" "P" (entlast))
(command "_layer" "set" "window" "")
(command "_rectangle" "885.415,-1935" "1034.585,-600")
(command "_rectangle" "885.415,2400" "1034.585,5300")
(command "_layer" "set" "grid" "")
(command "_rectangle" "886.415,-1934" "909.9433,-1909.2133")
(command "_array" "last" "" "R" "75" "3" "25.7867" "24.5283")
(command "_rectangle" "961,-1934" "984.5283,-1909.2133")
(command "_array" "last" "" "R" "75" "3" "25.7867" "24.5283")
(command "_rectangle" "886.415,1" "909.9433,25.7")
(command "_array" "last" "" "R" "70" "3" "25.7" "24.5283")
(command "_rectangle" "961,1" "984.5283,25.7")
(command "_array" "last" "" "R" "70" "3" "25.7" "24.5283")
(command "_rectangle" "886.415,1801" "909.9433,1825.9185")
(command "_array" "last" "" "R" "135" "3" "25.9185" "24.5283")
(command "_rectangle" "961,1801" "984.5283,1825.9185")
(command "_array" "last" "" "R" "135" "3" "25.9185" "24.5283")
(command "_layer" "set" "vgrooveFDA" "")
(command "_rectangle" "1034.585,-2233" "885.415,-1933")
(command "_layer" "set" "nitride" "")
(command "_layer" "set" "holes" "")
(command "_circle" "1037.085,331.5" "0.5")
(command "_array" "last" "" "R" "379" "1" "3" "2.5")
(command "_circle" "882.915,331.5" "0.5")
(command "_array" "last" "" "R" "379" "1" "3" "-2.5")
(command "_layer" "set" "nitride" "")
(command "_layer" "set" "window" "")
(command "_layer" "set" "window" "")
(command "_rectangle" "1039.585,0" "1200.415,1800")
(command "._fillet" "radius" "20" "._fillet" "P" (entlast))
(command "_layer" "set" "grid" "")
(command "_rectangle" "1040.585,1" "1062.4179,25.7")
(command "_array" "last" "" "R" "70" "7" "25.7" "22.8329")
(command "_layer" "set" "nitride" "")
; DRAWING REGION LAYER
(command "_layer" "set" "regionLayer3" "")
(command "_rectangle" "880,-460" "1040,2260")
(command "_layer" "set" "nitride" "")
(setq coupler3 nil)
(setq singlenanobeam3 nil)
(setq anglednodearray3 nil)
(setq cooledsinglenanobeam3 nil)
(setq yjunction3 nil)
; DEVICE #4
(command "_layer" "set" "window" "")
(command "_circle" "1192.915,-415" "5")
(command "_circle" "1192.915,-402.5" "5")
(command "_circle" "1192.915,-390" "5")
(command "_circle" "1192.915,-377.5" "5")
(command "_layer" "set" "nitride" "")
(setq currobj nil)
(setq currobj (ssadd))
; DRAWING COUPLER
(setq coords (list 
(list 1280.0645 -415) 
(list 1280.0645 -413) 
(list 1353.585 -413) 
(list 1353.585 -413) 
(list 1353.9677 -413.0761) 
(list 1354.2921 -413.2929) 
(list 1354.5089 -413.6173) 
(list 1354.585 -414) 
(list 1354.585 -411.8) 
(list 1354.585 -411.8) 
(list 1354.5089 -412.1827) 
(list 1354.2921 -412.5071) 
(list 1353.9677 -412.7239) 
(list 1353.585 -412.8) 
(list 1280.0645 -412.8) 
(list 1280.0645 -410.8) 
(list 1279.9355 -410.8) 
(list 1279.9355 -412.8) 
(list 1206.415 -412.8) 
(list 1206.0323 -412.7239) 
(list 1205.7079 -412.5071) 
(list 1205.4911 -412.1827) 
(list 1205.415 -411.8) 
(list 1205.415 -411.8) 
(list 1205.415 -414) 
(list 1205.4911 -413.6173) 
(list 1205.7079 -413.2929) 
(list 1206.0323 -413.0761) 
(list 1206.415 -413) 
(list 1206.415 -413) 
(list 1279.9355 -413) 
(list 1279.9355 -415)))
(apply 'command (append '("pline") coords '("c")))
(setq currobj (ssadd (entlast) currobj))
(command "._fillet" "radius" "0.3" "._fillet" "P" (entlast))
(command "_layer" "set" "holes" "")
(command "_circle" "1280,-412.9" "0.113")
(setq currobj (ssadd (entlast) currobj))
(command "_layer" "set" "nitride" "")
(command "_layer" "set" "text" "")
(command "_circle" "1279.2,-415" "0.075")
(command "_circle" "1279.2,-414.7" "0.075")
(command "_circle" "1279.2,-414.4" "0.075")
(command "_circle" "1278.9,-415" "0.075")
(command "_circle" "1278.9,-414.7" "0.075")
(command "_circle" "1278.9,-414.4" "0.075")
(command "_circle" "1278.6,-415" "0.075")
(command "_circle" "1278.6,-414.7" "0.075")
(command "_circle" "1278.6,-414.4" "0.075")
(command "_layer" "set" "nitride" "")
(command "_layer" "set" "prebias" "")
(command "_rectangle" "1205.415,-414" "1354.585,-411.8")
(setq currobj (ssadd (entlast) currobj))
(command "_rectangle" "1279.9355,-415" "1280.0645,-410.8")
(setq currobj (ssadd (entlast) currobj))
(command "_layer" "set" "nitride" "")
(setq coupler4 currobj)
(setq currobj nil)
(setq currobj (ssadd))
; DRAWING SINGLE NANOBEAM
(setq coords (list 
(list 1280.0645 -410.8) 
(list 1280.0645 -409.1417) 
(list 1280.0645 -407.4833) 
(list 1280.0645 -405.825) 
(list 1280.0645 -404.1667) 
(list 1280.0645 -402.5083) 
(list 1280.0645 -400.85) 
(list 1280.0645 -399.1917) 
(list 1280.0645 -397.5333) 
(list 1280.0646 -395.875) 
(list 1280.0646 -394.2167) 
(list 1280.0646 -392.5583) 
(list 1280.0646 -390.9) 
(list 1280.0647 -389.2417) 
(list 1280.0647 -387.5833) 
(list 1280.0647 -385.925) 
(list 1280.0648 -384.2667) 
(list 1280.0648 -382.6083) 
(list 1280.0649 -380.95) 
(list 1280.065 -379.2917) 
(list 1280.0651 -377.6333) 
(list 1280.0651 -375.975) 
(list 1280.0652 -374.3167) 
(list 1280.0653 -372.6583) 
(list 1280.0655 -371) 
(list 1280.0656 -369.3417) 
(list 1280.0657 -367.6833) 
(list 1280.0659 -366.025) 
(list 1280.066 -364.3667) 
(list 1280.0662 -362.7083) 
(list 1280.0664 -361.05) 
(list 1280.0666 -359.3917) 
(list 1280.0668 -357.7333) 
(list 1280.067 -356.075) 
(list 1280.0672 -354.4167) 
(list 1280.0675 -352.7583) 
(list 1280.0678 -351.1) 
(list 1280.068 -349.4417) 
(list 1280.0683 -347.7833) 
(list 1280.0686 -346.125) 
(list 1280.069 -344.4667) 
(list 1280.0693 -342.8083) 
(list 1280.0697 -341.15) 
(list 1280.07 -339.4917) 
(list 1280.0704 -337.8333) 
(list 1280.0709 -336.175) 
(list 1280.0713 -334.5167) 
(list 1280.0717 -332.8583) 
(list 1280.0722 -331.2) 
(list 1280.0727 -329.5417) 
(list 1280.0732 -327.8833) 
(list 1280.0738 -326.225) 
(list 1280.0743 -324.5667) 
(list 1280.0749 -322.9083) 
(list 1280.0755 -321.25) 
(list 1280.0761 -319.5917) 
(list 1280.0767 -317.9333) 
(list 1280.0774 -316.275) 
(list 1280.0781 -314.6167) 
(list 1280.0788 -312.9583) 
(list 1280.0796 -311.3) 
(list 1280.0803 -309.6417) 
(list 1280.0811 -307.9833) 
(list 1280.0819 -306.325) 
(list 1280.0828 -304.6667) 
(list 1280.0837 -303.0083) 
(list 1280.0845 -301.35) 
(list 1280.0855 -299.6917) 
(list 1280.0864 -298.0333) 
(list 1280.0874 -296.375) 
(list 1280.0884 -294.7167) 
(list 1280.0895 -293.0583) 
(list 1280.0905 -291.4) 
(list 1280.0916 -289.7417) 
(list 1280.0928 -288.0833) 
(list 1280.0939 -286.425) 
(list 1280.0951 -284.7667) 
(list 1280.0963 -283.1083) 
(list 1280.0976 -281.45) 
(list 1280.0989 -279.7917) 
(list 1280.1002 -278.1333) 
(list 1280.1016 -276.475) 
(list 1280.1029 -274.8167) 
(list 1280.1044 -273.1583) 
(list 1280.1058 -271.5) 
(list 1280.1073 -269.8417) 
(list 1280.1089 -268.1833) 
(list 1280.1104 -266.525) 
(list 1280.112 -264.8667) 
(list 1280.1137 -263.2083) 
(list 1280.1153 -261.55) 
(list 1280.117 -259.8917) 
(list 1280.1188 -258.2333) 
(list 1280.1206 -256.575) 
(list 1280.1224 -254.9167) 
(list 1280.1243 -253.2583) 
(list 1280.1262 -251.6) 
(list 1280.1281 -249.9417) 
(list 1280.1301 -248.2833) 
(list 1280.1322 -246.625) 
(list 1280.1342 -244.9667) 
(list 1280.1363 -243.3083) 
(list 1280.1385 -241.65) 
(list 1280.1407 -239.9917) 
(list 1280.1429 -238.3333) 
(list 1280.1452 -236.675) 
(list 1280.1476 -235.0167) 
(list 1280.1499 -233.3583) 
(list 1280.1523 -231.7) 
(list 1280.1548 -230.0417) 
(list 1280.1573 -228.3833) 
(list 1280.1599 -226.725) 
(list 1280.1625 -225.0667) 
(list 1280.1651 -223.4083) 
(list 1280.1678 -221.75) 
(list 1280.1706 -220.0917) 
(list 1280.1733 -218.4333) 
(list 1280.1762 -216.775) 
(list 1280.1791 -215.1167) 
(list 1280.182 -213.4583) 
(list 1280.185 -211.8) 
(list 1279.815 -211.8) 
(list 1279.818 -213.4583) 
(list 1279.8209 -215.1167) 
(list 1279.8238 -216.775) 
(list 1279.8267 -218.4333) 
(list 1279.8294 -220.0917) 
(list 1279.8322 -221.75) 
(list 1279.8349 -223.4083) 
(list 1279.8375 -225.0667) 
(list 1279.8401 -226.725) 
(list 1279.8427 -228.3833) 
(list 1279.8452 -230.0417) 
(list 1279.8477 -231.7) 
(list 1279.8501 -233.3583) 
(list 1279.8524 -235.0167) 
(list 1279.8548 -236.675) 
(list 1279.8571 -238.3333) 
(list 1279.8593 -239.9917) 
(list 1279.8615 -241.65) 
(list 1279.8637 -243.3083) 
(list 1279.8658 -244.9667) 
(list 1279.8678 -246.625) 
(list 1279.8699 -248.2833) 
(list 1279.8719 -249.9417) 
(list 1279.8738 -251.6) 
(list 1279.8757 -253.2583) 
(list 1279.8776 -254.9167) 
(list 1279.8794 -256.575) 
(list 1279.8812 -258.2333) 
(list 1279.883 -259.8917) 
(list 1279.8847 -261.55) 
(list 1279.8863 -263.2083) 
(list 1279.888 -264.8667) 
(list 1279.8896 -266.525) 
(list 1279.8911 -268.1833) 
(list 1279.8927 -269.8417) 
(list 1279.8942 -271.5) 
(list 1279.8956 -273.1583) 
(list 1279.8971 -274.8167) 
(list 1279.8984 -276.475) 
(list 1279.8998 -278.1333) 
(list 1279.9011 -279.7917) 
(list 1279.9024 -281.45) 
(list 1279.9037 -283.1083) 
(list 1279.9049 -284.7667) 
(list 1279.9061 -286.425) 
(list 1279.9072 -288.0833) 
(list 1279.9084 -289.7417) 
(list 1279.9095 -291.4) 
(list 1279.9105 -293.0583) 
(list 1279.9116 -294.7167) 
(list 1279.9126 -296.375) 
(list 1279.9136 -298.0333) 
(list 1279.9145 -299.6917) 
(list 1279.9155 -301.35) 
(list 1279.9163 -303.0083) 
(list 1279.9172 -304.6667) 
(list 1279.9181 -306.325) 
(list 1279.9189 -307.9833) 
(list 1279.9197 -309.6417) 
(list 1279.9204 -311.3) 
(list 1279.9212 -312.9583) 
(list 1279.9219 -314.6167) 
(list 1279.9226 -316.275) 
(list 1279.9233 -317.9333) 
(list 1279.9239 -319.5917) 
(list 1279.9245 -321.25) 
(list 1279.9251 -322.9083) 
(list 1279.9257 -324.5667) 
(list 1279.9262 -326.225) 
(list 1279.9268 -327.8833) 
(list 1279.9273 -329.5417) 
(list 1279.9278 -331.2) 
(list 1279.9283 -332.8583) 
(list 1279.9287 -334.5167) 
(list 1279.9291 -336.175) 
(list 1279.9296 -337.8333) 
(list 1279.93 -339.4917) 
(list 1279.9303 -341.15) 
(list 1279.9307 -342.8083) 
(list 1279.931 -344.4667) 
(list 1279.9314 -346.125) 
(list 1279.9317 -347.7833) 
(list 1279.932 -349.4417) 
(list 1279.9322 -351.1) 
(list 1279.9325 -352.7583) 
(list 1279.9328 -354.4167) 
(list 1279.933 -356.075) 
(list 1279.9332 -357.7333) 
(list 1279.9334 -359.3917) 
(list 1279.9336 -361.05) 
(list 1279.9338 -362.7083) 
(list 1279.934 -364.3667) 
(list 1279.9341 -366.025) 
(list 1279.9343 -367.6833) 
(list 1279.9344 -369.3417) 
(list 1279.9345 -371) 
(list 1279.9347 -372.6583) 
(list 1279.9348 -374.3167) 
(list 1279.9349 -375.975) 
(list 1279.9349 -377.6333) 
(list 1279.935 -379.2917) 
(list 1279.9351 -380.95) 
(list 1279.9352 -382.6083) 
(list 1279.9352 -384.2667) 
(list 1279.9353 -385.925) 
(list 1279.9353 -387.5833) 
(list 1279.9353 -389.2417) 
(list 1279.9354 -390.9) 
(list 1279.9354 -392.5583) 
(list 1279.9354 -394.2167) 
(list 1279.9354 -395.875) 
(list 1279.9355 -397.5333) 
(list 1279.9355 -399.1917) 
(list 1279.9355 -400.85) 
(list 1279.9355 -402.5083) 
(list 1279.9355 -404.1667) 
(list 1279.9355 -405.825) 
(list 1279.9355 -407.4833) 
(list 1279.9355 -409.1417) 
(list 1279.9355 -410.8)))
(apply 'command (append '("pline") coords '("c")))
(setq currobj (ssadd (entlast) currobj))
(command "_layer" "set" "prebias" "")
(command "_rectangle" "1279.815,-410.8" "1280.185,-211.8")
(setq currobj (ssadd (entlast) currobj))
(command "_layer" "set" "nitride" "")
(setq singlenanobeam4 currobj)
(setq currobj nil)
(setq currobj (ssadd))
; DRAWING NODE ARRAY
(setq coords (list 
(list 1280.185 -211.8) 
(list 1280.5625 -201.8) 
(list 1280.5625 -201.8) 
(list 1280.5625 -200.8) 
(list 1354.585 -212.6864) 
(list 1354.585 -207.7434) 
(list 1280.5625 -197.357) 
(list 1280.5625 -196.357) 
(list 1280.5625 -196.357) 
(list 1280.2625 -186.357) 
(list 1279.7375 -186.357) 
(list 1279.4375 -196.357) 
(list 1279.4375 -196.357) 
(list 1279.4375 -197.357) 
(list 1205.415 -207.7434) 
(list 1205.415 -212.6864) 
(list 1279.4375 -200.8) 
(list 1279.4375 -201.8) 
(list 1279.4375 -201.8) 
(list 1279.815 -211.8)))
(apply 'command (append '("pline") coords '("c")))
(setq currobj (ssadd (entlast) currobj))
(command "_layer" "set" "prebias" "")
(setq coords (list 
(list 1279.4375 -212.6864) 
(list 1279.4375 -200.8) 
(list 1205.415 -212.6864) 
(list 1205.415 -207.7434) 
(list 1279.4375 -197.357) 
(list 1279.4375 -186.357) 
(list 1280.5625 -186.357) 
(list 1280.5625 -197.357) 
(list 1354.585 -207.7434) 
(list 1354.585 -212.6864) 
(list 1280.5625 -200.8) 
(list 1280.5625 -212.6864)))
(apply 'command (append '("pline") coords '("c")))
(setq currobj (ssadd (entlast) currobj))
(command "_layer" "set" "nitride" "")
(command "_layer" "set" "fda1" "")
(setq coords (list 
(list 1280.5625 -200.657) 
(list 1354.585 -212.5434) 
(list 1354.585 -212.3664) 
(list 1280.5625 -200.58)))
(apply 'command (append '("pline") coords '("c")))
(setq currobj (ssadd (entlast) currobj))
(setq coords (list 
(list 1280.5625 -200.437) 
(list 1354.585 -212.2234) 
(list 1354.585 -212.0464) 
(list 1280.5625 -200.36)))
(apply 'command (append '("pline") coords '("c")))
(setq currobj (ssadd (entlast) currobj))
(setq coords (list 
(list 1280.5625 -200.217) 
(list 1354.585 -211.9034) 
(list 1354.585 -211.7264) 
(list 1280.5625 -200.14)))
(apply 'command (append '("pline") coords '("c")))
(setq currobj (ssadd (entlast) currobj))
(setq coords (list 
(list 1280.5625 -199.997) 
(list 1354.585 -211.5834) 
(list 1354.585 -211.4064) 
(list 1280.5625 -199.92)))
(apply 'command (append '("pline") coords '("c")))
(setq currobj (ssadd (entlast) currobj))
(setq coords (list 
(list 1280.5625 -199.777) 
(list 1354.585 -211.2634) 
(list 1354.585 -211.0864) 
(list 1280.5625 -199.7)))
(apply 'command (append '("pline") coords '("c")))
(setq currobj (ssadd (entlast) currobj))
(setq coords (list 
(list 1280.5625 -199.557) 
(list 1354.585 -210.9434) 
(list 1354.585 -210.7664) 
(list 1280.5625 -199.48)))
(apply 'command (append '("pline") coords '("c")))
(setq currobj (ssadd (entlast) currobj))
(setq coords (list 
(list 1280.5625 -199.337) 
(list 1354.585 -210.6234) 
(list 1354.585 -210.4464) 
(list 1280.5625 -199.26)))
(apply 'command (append '("pline") coords '("c")))
(setq currobj (ssadd (entlast) currobj))
(setq coords (list 
(list 1280.5625 -199.117) 
(list 1354.585 -210.3034) 
(list 1354.585 -210.1264) 
(list 1280.5625 -199.04)))
(apply 'command (append '("pline") coords '("c")))
(setq currobj (ssadd (entlast) currobj))
(setq coords (list 
(list 1280.5625 -198.897) 
(list 1354.585 -209.9834) 
(list 1354.585 -209.8064) 
(list 1280.5625 -198.82)))
(apply 'command (append '("pline") coords '("c")))
(setq currobj (ssadd (entlast) currobj))
(setq coords (list 
(list 1280.5625 -198.677) 
(list 1354.585 -209.6634) 
(list 1354.585 -209.4864) 
(list 1280.5625 -198.6)))
(apply 'command (append '("pline") coords '("c")))
(setq currobj (ssadd (entlast) currobj))
(setq coords (list 
(list 1280.5625 -198.457) 
(list 1354.585 -209.3434) 
(list 1354.585 -209.1664) 
(list 1280.5625 -198.38)))
(apply 'command (append '("pline") coords '("c")))
(setq currobj (ssadd (entlast) currobj))
(setq coords (list 
(list 1280.5625 -198.237) 
(list 1354.585 -209.0234) 
(list 1354.585 -208.8464) 
(list 1280.5625 -198.16)))
(apply 'command (append '("pline") coords '("c")))
(setq currobj (ssadd (entlast) currobj))
(setq coords (list 
(list 1280.5625 -198.017) 
(list 1354.585 -208.7034) 
(list 1354.585 -208.5264) 
(list 1280.5625 -197.94)))
(apply 'command (append '("pline") coords '("c")))
(setq currobj (ssadd (entlast) currobj))
(setq coords (list 
(list 1280.5625 -197.797) 
(list 1354.585 -208.3834) 
(list 1354.585 -208.2064) 
(list 1280.5625 -197.72)))
(apply 'command (append '("pline") coords '("c")))
(setq currobj (ssadd (entlast) currobj))
(setq coords (list 
(list 1280.5625 -197.577) 
(list 1354.585 -208.0634) 
(list 1354.585 -207.8864) 
(list 1280.5625 -197.5)))
(apply 'command (append '("pline") coords '("c")))
(setq currobj (ssadd (entlast) currobj))
(setq coords (list 
(list 1279.4375 -197.5) 
(list 1205.415 -207.8864) 
(list 1205.415 -208.0634) 
(list 1279.4375 -197.577)))
(apply 'command (append '("pline") coords '("c")))
(setq currobj (ssadd (entlast) currobj))
(setq coords (list 
(list 1279.4375 -197.72) 
(list 1205.415 -208.2064) 
(list 1205.415 -208.3834) 
(list 1279.4375 -197.797)))
(apply 'command (append '("pline") coords '("c")))
(setq currobj (ssadd (entlast) currobj))
(setq coords (list 
(list 1279.4375 -197.94) 
(list 1205.415 -208.5264) 
(list 1205.415 -208.7034) 
(list 1279.4375 -198.017)))
(apply 'command (append '("pline") coords '("c")))
(setq currobj (ssadd (entlast) currobj))
(setq coords (list 
(list 1279.4375 -198.16) 
(list 1205.415 -208.8464) 
(list 1205.415 -209.0234) 
(list 1279.4375 -198.237)))
(apply 'command (append '("pline") coords '("c")))
(setq currobj (ssadd (entlast) currobj))
(setq coords (list 
(list 1279.4375 -198.38) 
(list 1205.415 -209.1664) 
(list 1205.415 -209.3434) 
(list 1279.4375 -198.457)))
(apply 'command (append '("pline") coords '("c")))
(setq currobj (ssadd (entlast) currobj))
(setq coords (list 
(list 1279.4375 -198.6) 
(list 1205.415 -209.4864) 
(list 1205.415 -209.6634) 
(list 1279.4375 -198.677)))
(apply 'command (append '("pline") coords '("c")))
(setq currobj (ssadd (entlast) currobj))
(setq coords (list 
(list 1279.4375 -198.82) 
(list 1205.415 -209.8064) 
(list 1205.415 -209.9834) 
(list 1279.4375 -198.897)))
(apply 'command (append '("pline") coords '("c")))
(setq currobj (ssadd (entlast) currobj))
(setq coords (list 
(list 1279.4375 -199.04) 
(list 1205.415 -210.1264) 
(list 1205.415 -210.3034) 
(list 1279.4375 -199.117)))
(apply 'command (append '("pline") coords '("c")))
(setq currobj (ssadd (entlast) currobj))
(setq coords (list 
(list 1279.4375 -199.26) 
(list 1205.415 -210.4464) 
(list 1205.415 -210.6234) 
(list 1279.4375 -199.337)))
(apply 'command (append '("pline") coords '("c")))
(setq currobj (ssadd (entlast) currobj))
(setq coords (list 
(list 1279.4375 -199.48) 
(list 1205.415 -210.7664) 
(list 1205.415 -210.9434) 
(list 1279.4375 -199.557)))
(apply 'command (append '("pline") coords '("c")))
(setq currobj (ssadd (entlast) currobj))
(setq coords (list 
(list 1279.4375 -199.7) 
(list 1205.415 -211.0864) 
(list 1205.415 -211.2634) 
(list 1279.4375 -199.777)))
(apply 'command (append '("pline") coords '("c")))
(setq currobj (ssadd (entlast) currobj))
(setq coords (list 
(list 1279.4375 -199.92) 
(list 1205.415 -211.4064) 
(list 1205.415 -211.5834) 
(list 1279.4375 -199.997)))
(apply 'command (append '("pline") coords '("c")))
(setq currobj (ssadd (entlast) currobj))
(setq coords (list 
(list 1279.4375 -200.14) 
(list 1205.415 -211.7264) 
(list 1205.415 -211.9034) 
(list 1279.4375 -200.217)))
(apply 'command (append '("pline") coords '("c")))
(setq currobj (ssadd (entlast) currobj))
(setq coords (list 
(list 1279.4375 -200.36) 
(list 1205.415 -212.0464) 
(list 1205.415 -212.2234) 
(list 1279.4375 -200.437)))
(apply 'command (append '("pline") coords '("c")))
(setq currobj (ssadd (entlast) currobj))
(setq coords (list 
(list 1279.4375 -200.58) 
(list 1205.415 -212.3664) 
(list 1205.415 -212.5434) 
(list 1279.4375 -200.657)))
(apply 'command (append '("pline") coords '("c")))
(setq currobj (ssadd (entlast) currobj))
(command "_layer" "set" "nitride" "")
(command "_layer" "set" "text" "")
(command "_circle" "1278.985,-211.8" "0.075")
(command "_circle" "1278.985,-211.5" "0.075")
(command "_circle" "1278.985,-211.2" "0.075")
(command "_circle" "1278.985,-210.9" "0.075")
(command "_circle" "1278.985,-210.6" "0.075")
(command "_circle" "1278.685,-211.8" "0.075")
(command "_circle" "1278.685,-211.5" "0.075")
(command "_circle" "1278.685,-211.2" "0.075")
(command "_circle" "1278.685,-210.9" "0.075")
(command "_circle" "1278.685,-210.6" "0.075")
(command "_circle" "1278.385,-211.8" "0.075")
(command "_circle" "1278.385,-211.5" "0.075")
(command "_circle" "1278.385,-211.2" "0.075")
(command "_circle" "1278.385,-210.9" "0.075")
(command "_circle" "1278.385,-210.6" "0.075")
(command "_circle" "1278.085,-211.8" "0.075")
(command "_circle" "1278.085,-211.5" "0.075")
(command "_circle" "1278.085,-211.2" "0.075")
(command "_circle" "1278.085,-210.9" "0.075")
(command "_circle" "1278.085,-210.6" "0.075")
(command "_circle" "1277.785,-211.8" "0.075")
(command "_circle" "1277.785,-211.5" "0.075")
(command "_circle" "1277.785,-211.2" "0.075")
(command "_circle" "1277.785,-210.9" "0.075")
(command "_circle" "1277.785,-210.6" "0.075")
(command "_layer" "set" "nitride" "")
(setq anglednodearray4 currobj)
(setq currobj nil)
(setq currobj (ssadd))
; DRAWING COOLED SINGLE NANOBEAM
(setq coords (list 
(list 1280.2625 -186.357) 
(list 1280.2625 -181.357) 
(list 1279.7375 -181.357) 
(list 1279.7375 -186.357)))
(apply 'command (append '("pline") coords '("c")))
(setq currobj (ssadd (entlast) currobj))
(command "_layer" "set" "prebias" "")
(command "_rectangle" "1279.7375,-186.357" "1280.2625,-181.357")
(setq currobj (ssadd (entlast) currobj))
(command "_layer" "set" "nitride" "")
(setq coords (list 
(list 1280.2625 -181.357) 
(list 1280.5625 -171.357) 
(list 1280.5625 -171.357) 
(list 1280.5625 -170.357) 
(list 1354.585 -171.107) 
(list 1354.585 -166.164) 
(list 1280.5625 -166.914) 
(list 1280.5625 -165.914) 
(list 1280.5625 -165.914) 
(list 1280.2625 -155.914) 
(list 1279.7375 -155.914) 
(list 1279.4375 -165.914) 
(list 1279.4375 -165.914) 
(list 1279.4375 -166.914) 
(list 1205.415 -166.164) 
(list 1205.415 -171.107) 
(list 1279.4375 -170.357) 
(list 1279.4375 -171.357) 
(list 1279.4375 -171.357) 
(list 1279.7375 -181.357)))
(apply 'command (append '("pline") coords '("c")))
(setq currobj (ssadd (entlast) currobj))
(command "_layer" "set" "prebias" "")
(setq coords (list 
(list 1279.4375 -181.357) 
(list 1279.4375 -170.357) 
(list 1205.415 -171.107) 
(list 1205.415 -166.164) 
(list 1279.4375 -166.914) 
(list 1279.4375 -155.914) 
(list 1280.5625 -155.914) 
(list 1280.5625 -166.914) 
(list 1354.585 -166.164) 
(list 1354.585 -171.107) 
(list 1280.5625 -170.357) 
(list 1280.5625 -181.357)))
(apply 'command (append '("pline") coords '("c")))
(setq currobj (ssadd (entlast) currobj))
(command "_layer" "set" "nitride" "")
(command "_layer" "set" "fda1" "")
(setq coords (list 
(list 1280.5625 -170.214) 
(list 1354.585 -170.964) 
(list 1354.585 -170.787) 
(list 1280.5625 -170.137)))
(apply 'command (append '("pline") coords '("c")))
(setq currobj (ssadd (entlast) currobj))
(setq coords (list 
(list 1280.5625 -169.994) 
(list 1354.585 -170.644) 
(list 1354.585 -170.467) 
(list 1280.5625 -169.917)))
(apply 'command (append '("pline") coords '("c")))
(setq currobj (ssadd (entlast) currobj))
(setq coords (list 
(list 1280.5625 -169.774) 
(list 1354.585 -170.324) 
(list 1354.585 -170.147) 
(list 1280.5625 -169.697)))
(apply 'command (append '("pline") coords '("c")))
(setq currobj (ssadd (entlast) currobj))
(setq coords (list 
(list 1280.5625 -169.554) 
(list 1354.585 -170.004) 
(list 1354.585 -169.827) 
(list 1280.5625 -169.477)))
(apply 'command (append '("pline") coords '("c")))
(setq currobj (ssadd (entlast) currobj))
(setq coords (list 
(list 1280.5625 -169.334) 
(list 1354.585 -169.684) 
(list 1354.585 -169.507) 
(list 1280.5625 -169.257)))
(apply 'command (append '("pline") coords '("c")))
(setq currobj (ssadd (entlast) currobj))
(setq coords (list 
(list 1280.5625 -169.114) 
(list 1354.585 -169.364) 
(list 1354.585 -169.187) 
(list 1280.5625 -169.037)))
(apply 'command (append '("pline") coords '("c")))
(setq currobj (ssadd (entlast) currobj))
(setq coords (list 
(list 1280.5625 -168.894) 
(list 1354.585 -169.044) 
(list 1354.585 -168.867) 
(list 1280.5625 -168.817)))
(apply 'command (append '("pline") coords '("c")))
(setq currobj (ssadd (entlast) currobj))
(setq coords (list 
(list 1280.5625 -168.674) 
(list 1354.585 -168.724) 
(list 1354.585 -168.547) 
(list 1280.5625 -168.597)))
(apply 'command (append '("pline") coords '("c")))
(setq currobj (ssadd (entlast) currobj))
(setq coords (list 
(list 1280.5625 -168.454) 
(list 1354.585 -168.404) 
(list 1354.585 -168.227) 
(list 1280.5625 -168.377)))
(apply 'command (append '("pline") coords '("c")))
(setq currobj (ssadd (entlast) currobj))
(setq coords (list 
(list 1280.5625 -168.234) 
(list 1354.585 -168.084) 
(list 1354.585 -167.907) 
(list 1280.5625 -168.157)))
(apply 'command (append '("pline") coords '("c")))
(setq currobj (ssadd (entlast) currobj))
(setq coords (list 
(list 1280.5625 -168.014) 
(list 1354.585 -167.764) 
(list 1354.585 -167.587) 
(list 1280.5625 -167.937)))
(apply 'command (append '("pline") coords '("c")))
(setq currobj (ssadd (entlast) currobj))
(setq coords (list 
(list 1280.5625 -167.794) 
(list 1354.585 -167.444) 
(list 1354.585 -167.267) 
(list 1280.5625 -167.717)))
(apply 'command (append '("pline") coords '("c")))
(setq currobj (ssadd (entlast) currobj))
(setq coords (list 
(list 1280.5625 -167.574) 
(list 1354.585 -167.124) 
(list 1354.585 -166.947) 
(list 1280.5625 -167.497)))
(apply 'command (append '("pline") coords '("c")))
(setq currobj (ssadd (entlast) currobj))
(setq coords (list 
(list 1280.5625 -167.354) 
(list 1354.585 -166.804) 
(list 1354.585 -166.627) 
(list 1280.5625 -167.277)))
(apply 'command (append '("pline") coords '("c")))
(setq currobj (ssadd (entlast) currobj))
(setq coords (list 
(list 1280.5625 -167.134) 
(list 1354.585 -166.484) 
(list 1354.585 -166.307) 
(list 1280.5625 -167.057)))
(apply 'command (append '("pline") coords '("c")))
(setq currobj (ssadd (entlast) currobj))
(setq coords (list 
(list 1279.4375 -167.057) 
(list 1205.415 -166.307) 
(list 1205.415 -166.484) 
(list 1279.4375 -167.134)))
(apply 'command (append '("pline") coords '("c")))
(setq currobj (ssadd (entlast) currobj))
(setq coords (list 
(list 1279.4375 -167.277) 
(list 1205.415 -166.627) 
(list 1205.415 -166.804) 
(list 1279.4375 -167.354)))
(apply 'command (append '("pline") coords '("c")))
(setq currobj (ssadd (entlast) currobj))
(setq coords (list 
(list 1279.4375 -167.497) 
(list 1205.415 -166.947) 
(list 1205.415 -167.124) 
(list 1279.4375 -167.574)))
(apply 'command (append '("pline") coords '("c")))
(setq currobj (ssadd (entlast) currobj))
(setq coords (list 
(list 1279.4375 -167.717) 
(list 1205.415 -167.267) 
(list 1205.415 -167.444) 
(list 1279.4375 -167.794)))
(apply 'command (append '("pline") coords '("c")))
(setq currobj (ssadd (entlast) currobj))
(setq coords (list 
(list 1279.4375 -167.937) 
(list 1205.415 -167.587) 
(list 1205.415 -167.764) 
(list 1279.4375 -168.014)))
(apply 'command (append '("pline") coords '("c")))
(setq currobj (ssadd (entlast) currobj))
(setq coords (list 
(list 1279.4375 -168.157) 
(list 1205.415 -167.907) 
(list 1205.415 -168.084) 
(list 1279.4375 -168.234)))
(apply 'command (append '("pline") coords '("c")))
(setq currobj (ssadd (entlast) currobj))
(setq coords (list 
(list 1279.4375 -168.377) 
(list 1205.415 -168.227) 
(list 1205.415 -168.404) 
(list 1279.4375 -168.454)))
(apply 'command (append '("pline") coords '("c")))
(setq currobj (ssadd (entlast) currobj))
(setq coords (list 
(list 1279.4375 -168.597) 
(list 1205.415 -168.547) 
(list 1205.415 -168.724) 
(list 1279.4375 -168.674)))
(apply 'command (append '("pline") coords '("c")))
(setq currobj (ssadd (entlast) currobj))
(setq coords (list 
(list 1279.4375 -168.817) 
(list 1205.415 -168.867) 
(list 1205.415 -169.044) 
(list 1279.4375 -168.894)))
(apply 'command (append '("pline") coords '("c")))
(setq currobj (ssadd (entlast) currobj))
(setq coords (list 
(list 1279.4375 -169.037) 
(list 1205.415 -169.187) 
(list 1205.415 -169.364) 
(list 1279.4375 -169.114)))
(apply 'command (append '("pline") coords '("c")))
(setq currobj (ssadd (entlast) currobj))
(setq coords (list 
(list 1279.4375 -169.257) 
(list 1205.415 -169.507) 
(list 1205.415 -169.684) 
(list 1279.4375 -169.334)))
(apply 'command (append '("pline") coords '("c")))
(setq currobj (ssadd (entlast) currobj))
(setq coords (list 
(list 1279.4375 -169.477) 
(list 1205.415 -169.827) 
(list 1205.415 -170.004) 
(list 1279.4375 -169.554)))
(apply 'command (append '("pline") coords '("c")))
(setq currobj (ssadd (entlast) currobj))
(setq coords (list 
(list 1279.4375 -169.697) 
(list 1205.415 -170.147) 
(list 1205.415 -170.324) 
(list 1279.4375 -169.774)))
(apply 'command (append '("pline") coords '("c")))
(setq currobj (ssadd (entlast) currobj))
(setq coords (list 
(list 1279.4375 -169.917) 
(list 1205.415 -170.467) 
(list 1205.415 -170.644) 
(list 1279.4375 -169.994)))
(apply 'command (append '("pline") coords '("c")))
(setq currobj (ssadd (entlast) currobj))
(setq coords (list 
(list 1279.4375 -170.137) 
(list 1205.415 -170.787) 
(list 1205.415 -170.964) 
(list 1279.4375 -170.214)))
(apply 'command (append '("pline") coords '("c")))
(setq currobj (ssadd (entlast) currobj))
(command "_layer" "set" "nitride" "")
(command "_layer" "set" "text" "")
(command "_circle" "1279.0625,-181.357" "0.075")
(command "_circle" "1279.0625,-181.057" "0.075")
(command "_circle" "1279.0625,-180.757" "0.075")
(command "_circle" "1279.0625,-180.457" "0.075")
(command "_circle" "1279.0625,-180.157" "0.075")
(command "_circle" "1278.7625,-181.357" "0.075")
(command "_circle" "1278.7625,-181.057" "0.075")
(command "_circle" "1278.7625,-180.757" "0.075")
(command "_circle" "1278.7625,-180.457" "0.075")
(command "_circle" "1278.7625,-180.157" "0.075")
(command "_circle" "1278.4625,-181.357" "0.075")
(command "_circle" "1278.4625,-181.057" "0.075")
(command "_circle" "1278.4625,-180.757" "0.075")
(command "_circle" "1278.4625,-180.457" "0.075")
(command "_circle" "1278.4625,-180.157" "0.075")
(command "_circle" "1278.1625,-181.357" "0.075")
(command "_circle" "1278.1625,-181.057" "0.075")
(command "_circle" "1278.1625,-180.757" "0.075")
(command "_circle" "1278.1625,-180.457" "0.075")
(command "_circle" "1278.1625,-180.157" "0.075")
(command "_circle" "1277.8625,-181.357" "0.075")
(command "_circle" "1277.8625,-181.057" "0.075")
(command "_circle" "1277.8625,-180.757" "0.075")
(command "_circle" "1277.8625,-180.457" "0.075")
(command "_circle" "1277.8625,-180.157" "0.075")
(command "_layer" "set" "nitride" "")
(setq coords (list 
(list 1280.2625 -155.914) 
(list 1280.2625 -40.2693) 
(list 1279.7375 -40.2693) 
(list 1279.7375 -155.914)))
(apply 'command (append '("pline") coords '("c")))
(setq currobj (ssadd (entlast) currobj))
(command "_layer" "set" "prebias" "")
(command "_rectangle" "1279.7375,-155.914" "1280.2625,-40.2693")
(setq currobj (ssadd (entlast) currobj))
(command "_layer" "set" "nitride" "")
(setq coords (list 
(list 1280.2625 -40.2693) 
(list 1280.5625 -30.2693) 
(list 1280.5625 -30.2693) 
(list 1280.5625 -29.2693) 
(list 1354.585 -30.0193) 
(list 1354.585 -25.0763) 
(list 1280.5625 -25.8263) 
(list 1280.5625 -24.8263) 
(list 1280.5625 -24.8263) 
(list 1280.2625 -14.8263) 
(list 1279.7375 -14.8263) 
(list 1279.4375 -24.8263) 
(list 1279.4375 -24.8263) 
(list 1279.4375 -25.8263) 
(list 1205.415 -25.0763) 
(list 1205.415 -30.0193) 
(list 1279.4375 -29.2693) 
(list 1279.4375 -30.2693) 
(list 1279.4375 -30.2693) 
(list 1279.7375 -40.2693)))
(apply 'command (append '("pline") coords '("c")))
(setq currobj (ssadd (entlast) currobj))
(command "_layer" "set" "prebias" "")
(setq coords (list 
(list 1279.4375 -40.2693) 
(list 1279.4375 -29.2693) 
(list 1205.415 -30.0193) 
(list 1205.415 -25.0763) 
(list 1279.4375 -25.8263) 
(list 1279.4375 -14.8263) 
(list 1280.5625 -14.8263) 
(list 1280.5625 -25.8263) 
(list 1354.585 -25.0763) 
(list 1354.585 -30.0193) 
(list 1280.5625 -29.2693) 
(list 1280.5625 -40.2693)))
(apply 'command (append '("pline") coords '("c")))
(setq currobj (ssadd (entlast) currobj))
(command "_layer" "set" "nitride" "")
(command "_layer" "set" "fda1" "")
(setq coords (list 
(list 1280.5625 -29.1263) 
(list 1354.585 -29.8763) 
(list 1354.585 -29.6993) 
(list 1280.5625 -29.0493)))
(apply 'command (append '("pline") coords '("c")))
(setq currobj (ssadd (entlast) currobj))
(setq coords (list 
(list 1280.5625 -28.9063) 
(list 1354.585 -29.5563) 
(list 1354.585 -29.3793) 
(list 1280.5625 -28.8293)))
(apply 'command (append '("pline") coords '("c")))
(setq currobj (ssadd (entlast) currobj))
(setq coords (list 
(list 1280.5625 -28.6863) 
(list 1354.585 -29.2363) 
(list 1354.585 -29.0593) 
(list 1280.5625 -28.6093)))
(apply 'command (append '("pline") coords '("c")))
(setq currobj (ssadd (entlast) currobj))
(setq coords (list 
(list 1280.5625 -28.4663) 
(list 1354.585 -28.9163) 
(list 1354.585 -28.7393) 
(list 1280.5625 -28.3893)))
(apply 'command (append '("pline") coords '("c")))
(setq currobj (ssadd (entlast) currobj))
(setq coords (list 
(list 1280.5625 -28.2463) 
(list 1354.585 -28.5963) 
(list 1354.585 -28.4193) 
(list 1280.5625 -28.1693)))
(apply 'command (append '("pline") coords '("c")))
(setq currobj (ssadd (entlast) currobj))
(setq coords (list 
(list 1280.5625 -28.0263) 
(list 1354.585 -28.2763) 
(list 1354.585 -28.0993) 
(list 1280.5625 -27.9493)))
(apply 'command (append '("pline") coords '("c")))
(setq currobj (ssadd (entlast) currobj))
(setq coords (list 
(list 1280.5625 -27.8063) 
(list 1354.585 -27.9563) 
(list 1354.585 -27.7793) 
(list 1280.5625 -27.7293)))
(apply 'command (append '("pline") coords '("c")))
(setq currobj (ssadd (entlast) currobj))
(setq coords (list 
(list 1280.5625 -27.5863) 
(list 1354.585 -27.6363) 
(list 1354.585 -27.4593) 
(list 1280.5625 -27.5093)))
(apply 'command (append '("pline") coords '("c")))
(setq currobj (ssadd (entlast) currobj))
(setq coords (list 
(list 1280.5625 -27.3663) 
(list 1354.585 -27.3163) 
(list 1354.585 -27.1393) 
(list 1280.5625 -27.2893)))
(apply 'command (append '("pline") coords '("c")))
(setq currobj (ssadd (entlast) currobj))
(setq coords (list 
(list 1280.5625 -27.1463) 
(list 1354.585 -26.9963) 
(list 1354.585 -26.8193) 
(list 1280.5625 -27.0693)))
(apply 'command (append '("pline") coords '("c")))
(setq currobj (ssadd (entlast) currobj))
(setq coords (list 
(list 1280.5625 -26.9263) 
(list 1354.585 -26.6763) 
(list 1354.585 -26.4993) 
(list 1280.5625 -26.8493)))
(apply 'command (append '("pline") coords '("c")))
(setq currobj (ssadd (entlast) currobj))
(setq coords (list 
(list 1280.5625 -26.7063) 
(list 1354.585 -26.3563) 
(list 1354.585 -26.1793) 
(list 1280.5625 -26.6293)))
(apply 'command (append '("pline") coords '("c")))
(setq currobj (ssadd (entlast) currobj))
(setq coords (list 
(list 1280.5625 -26.4863) 
(list 1354.585 -26.0363) 
(list 1354.585 -25.8593) 
(list 1280.5625 -26.4093)))
(apply 'command (append '("pline") coords '("c")))
(setq currobj (ssadd (entlast) currobj))
(setq coords (list 
(list 1280.5625 -26.2663) 
(list 1354.585 -25.7163) 
(list 1354.585 -25.5393) 
(list 1280.5625 -26.1893)))
(apply 'command (append '("pline") coords '("c")))
(setq currobj (ssadd (entlast) currobj))
(setq coords (list 
(list 1280.5625 -26.0463) 
(list 1354.585 -25.3963) 
(list 1354.585 -25.2193) 
(list 1280.5625 -25.9693)))
(apply 'command (append '("pline") coords '("c")))
(setq currobj (ssadd (entlast) currobj))
(setq coords (list 
(list 1279.4375 -25.9693) 
(list 1205.415 -25.2193) 
(list 1205.415 -25.3963) 
(list 1279.4375 -26.0463)))
(apply 'command (append '("pline") coords '("c")))
(setq currobj (ssadd (entlast) currobj))
(setq coords (list 
(list 1279.4375 -26.1893) 
(list 1205.415 -25.5393) 
(list 1205.415 -25.7163) 
(list 1279.4375 -26.2663)))
(apply 'command (append '("pline") coords '("c")))
(setq currobj (ssadd (entlast) currobj))
(setq coords (list 
(list 1279.4375 -26.4093) 
(list 1205.415 -25.8593) 
(list 1205.415 -26.0363) 
(list 1279.4375 -26.4863)))
(apply 'command (append '("pline") coords '("c")))
(setq currobj (ssadd (entlast) currobj))
(setq coords (list 
(list 1279.4375 -26.6293) 
(list 1205.415 -26.1793) 
(list 1205.415 -26.3563) 
(list 1279.4375 -26.7063)))
(apply 'command (append '("pline") coords '("c")))
(setq currobj (ssadd (entlast) currobj))
(setq coords (list 
(list 1279.4375 -26.8493) 
(list 1205.415 -26.4993) 
(list 1205.415 -26.6763) 
(list 1279.4375 -26.9263)))
(apply 'command (append '("pline") coords '("c")))
(setq currobj (ssadd (entlast) currobj))
(setq coords (list 
(list 1279.4375 -27.0693) 
(list 1205.415 -26.8193) 
(list 1205.415 -26.9963) 
(list 1279.4375 -27.1463)))
(apply 'command (append '("pline") coords '("c")))
(setq currobj (ssadd (entlast) currobj))
(setq coords (list 
(list 1279.4375 -27.2893) 
(list 1205.415 -27.1393) 
(list 1205.415 -27.3163) 
(list 1279.4375 -27.3663)))
(apply 'command (append '("pline") coords '("c")))
(setq currobj (ssadd (entlast) currobj))
(setq coords (list 
(list 1279.4375 -27.5093) 
(list 1205.415 -27.4593) 
(list 1205.415 -27.6363) 
(list 1279.4375 -27.5863)))
(apply 'command (append '("pline") coords '("c")))
(setq currobj (ssadd (entlast) currobj))
(setq coords (list 
(list 1279.4375 -27.7293) 
(list 1205.415 -27.7793) 
(list 1205.415 -27.9563) 
(list 1279.4375 -27.8063)))
(apply 'command (append '("pline") coords '("c")))
(setq currobj (ssadd (entlast) currobj))
(setq coords (list 
(list 1279.4375 -27.9493) 
(list 1205.415 -28.0993) 
(list 1205.415 -28.2763) 
(list 1279.4375 -28.0263)))
(apply 'command (append '("pline") coords '("c")))
(setq currobj (ssadd (entlast) currobj))
(setq coords (list 
(list 1279.4375 -28.1693) 
(list 1205.415 -28.4193) 
(list 1205.415 -28.5963) 
(list 1279.4375 -28.2463)))
(apply 'command (append '("pline") coords '("c")))
(setq currobj (ssadd (entlast) currobj))
(setq coords (list 
(list 1279.4375 -28.3893) 
(list 1205.415 -28.7393) 
(list 1205.415 -28.9163) 
(list 1279.4375 -28.4663)))
(apply 'command (append '("pline") coords '("c")))
(setq currobj (ssadd (entlast) currobj))
(setq coords (list 
(list 1279.4375 -28.6093) 
(list 1205.415 -29.0593) 
(list 1205.415 -29.2363) 
(list 1279.4375 -28.6863)))
(apply 'command (append '("pline") coords '("c")))
(setq currobj (ssadd (entlast) currobj))
(setq coords (list 
(list 1279.4375 -28.8293) 
(list 1205.415 -29.3793) 
(list 1205.415 -29.5563) 
(list 1279.4375 -28.9063)))
(apply 'command (append '("pline") coords '("c")))
(setq currobj (ssadd (entlast) currobj))
(setq coords (list 
(list 1279.4375 -29.0493) 
(list 1205.415 -29.6993) 
(list 1205.415 -29.8763) 
(list 1279.4375 -29.1263)))
(apply 'command (append '("pline") coords '("c")))
(setq currobj (ssadd (entlast) currobj))
(command "_layer" "set" "nitride" "")
(command "_layer" "set" "text" "")
(command "_circle" "1279.0625,-40.2693" "0.075")
(command "_circle" "1279.0625,-39.9693" "0.075")
(command "_circle" "1279.0625,-39.6693" "0.075")
(command "_circle" "1279.0625,-39.3693" "0.075")
(command "_circle" "1279.0625,-39.0693" "0.075")
(command "_circle" "1278.7625,-40.2693" "0.075")
(command "_circle" "1278.7625,-39.9693" "0.075")
(command "_circle" "1278.7625,-39.6693" "0.075")
(command "_circle" "1278.7625,-39.3693" "0.075")
(command "_circle" "1278.7625,-39.0693" "0.075")
(command "_circle" "1278.4625,-40.2693" "0.075")
(command "_circle" "1278.4625,-39.9693" "0.075")
(command "_circle" "1278.4625,-39.6693" "0.075")
(command "_circle" "1278.4625,-39.3693" "0.075")
(command "_circle" "1278.4625,-39.0693" "0.075")
(command "_circle" "1278.1625,-40.2693" "0.075")
(command "_circle" "1278.1625,-39.9693" "0.075")
(command "_circle" "1278.1625,-39.6693" "0.075")
(command "_circle" "1278.1625,-39.3693" "0.075")
(command "_circle" "1278.1625,-39.0693" "0.075")
(command "_circle" "1277.8625,-40.2693" "0.075")
(command "_circle" "1277.8625,-39.9693" "0.075")
(command "_circle" "1277.8625,-39.6693" "0.075")
(command "_circle" "1277.8625,-39.3693" "0.075")
(command "_circle" "1277.8625,-39.0693" "0.075")
(command "_layer" "set" "nitride" "")
(setq coords (list 
(list 1280.2625 -14.8263) 
(list 1280.2625 100.8184) 
(list 1279.7375 100.8184) 
(list 1279.7375 -14.8263)))
(apply 'command (append '("pline") coords '("c")))
(setq currobj (ssadd (entlast) currobj))
(command "_layer" "set" "prebias" "")
(command "_rectangle" "1279.7375,-14.8263" "1280.2625,100.8184")
(setq currobj (ssadd (entlast) currobj))
(command "_layer" "set" "nitride" "")
(setq coords (list 
(list 1280.2625 100.8184) 
(list 1280.5625 110.8184) 
(list 1280.5625 110.8184) 
(list 1280.5625 111.8184) 
(list 1354.585 111.0684) 
(list 1354.585 116.0114) 
(list 1280.5625 115.2614) 
(list 1280.5625 116.2614) 
(list 1280.5625 116.2614) 
(list 1280.2625 126.2614) 
(list 1279.7375 126.2614) 
(list 1279.4375 116.2614) 
(list 1279.4375 116.2614) 
(list 1279.4375 115.2614) 
(list 1205.415 116.0114) 
(list 1205.415 111.0684) 
(list 1279.4375 111.8184) 
(list 1279.4375 110.8184) 
(list 1279.4375 110.8184) 
(list 1279.7375 100.8184)))
(apply 'command (append '("pline") coords '("c")))
(setq currobj (ssadd (entlast) currobj))
(command "_layer" "set" "prebias" "")
(setq coords (list 
(list 1279.4375 100.8184) 
(list 1279.4375 111.8184) 
(list 1205.415 111.0684) 
(list 1205.415 116.0114) 
(list 1279.4375 115.2614) 
(list 1279.4375 126.2614) 
(list 1280.5625 126.2614) 
(list 1280.5625 115.2614) 
(list 1354.585 116.0114) 
(list 1354.585 111.0684) 
(list 1280.5625 111.8184) 
(list 1280.5625 100.8184)))
(apply 'command (append '("pline") coords '("c")))
(setq currobj (ssadd (entlast) currobj))
(command "_layer" "set" "nitride" "")
(command "_layer" "set" "fda1" "")
(setq coords (list 
(list 1280.5625 111.9614) 
(list 1354.585 111.2114) 
(list 1354.585 111.3884) 
(list 1280.5625 112.0384)))
(apply 'command (append '("pline") coords '("c")))
(setq currobj (ssadd (entlast) currobj))
(setq coords (list 
(list 1280.5625 112.1814) 
(list 1354.585 111.5314) 
(list 1354.585 111.7084) 
(list 1280.5625 112.2584)))
(apply 'command (append '("pline") coords '("c")))
(setq currobj (ssadd (entlast) currobj))
(setq coords (list 
(list 1280.5625 112.4014) 
(list 1354.585 111.8514) 
(list 1354.585 112.0284) 
(list 1280.5625 112.4784)))
(apply 'command (append '("pline") coords '("c")))
(setq currobj (ssadd (entlast) currobj))
(setq coords (list 
(list 1280.5625 112.6214) 
(list 1354.585 112.1714) 
(list 1354.585 112.3484) 
(list 1280.5625 112.6984)))
(apply 'command (append '("pline") coords '("c")))
(setq currobj (ssadd (entlast) currobj))
(setq coords (list 
(list 1280.5625 112.8414) 
(list 1354.585 112.4914) 
(list 1354.585 112.6684) 
(list 1280.5625 112.9184)))
(apply 'command (append '("pline") coords '("c")))
(setq currobj (ssadd (entlast) currobj))
(setq coords (list 
(list 1280.5625 113.0614) 
(list 1354.585 112.8114) 
(list 1354.585 112.9884) 
(list 1280.5625 113.1384)))
(apply 'command (append '("pline") coords '("c")))
(setq currobj (ssadd (entlast) currobj))
(setq coords (list 
(list 1280.5625 113.2814) 
(list 1354.585 113.1314) 
(list 1354.585 113.3084) 
(list 1280.5625 113.3584)))
(apply 'command (append '("pline") coords '("c")))
(setq currobj (ssadd (entlast) currobj))
(setq coords (list 
(list 1280.5625 113.5014) 
(list 1354.585 113.4514) 
(list 1354.585 113.6284) 
(list 1280.5625 113.5784)))
(apply 'command (append '("pline") coords '("c")))
(setq currobj (ssadd (entlast) currobj))
(setq coords (list 
(list 1280.5625 113.7214) 
(list 1354.585 113.7714) 
(list 1354.585 113.9484) 
(list 1280.5625 113.7984)))
(apply 'command (append '("pline") coords '("c")))
(setq currobj (ssadd (entlast) currobj))
(setq coords (list 
(list 1280.5625 113.9414) 
(list 1354.585 114.0914) 
(list 1354.585 114.2684) 
(list 1280.5625 114.0184)))
(apply 'command (append '("pline") coords '("c")))
(setq currobj (ssadd (entlast) currobj))
(setq coords (list 
(list 1280.5625 114.1614) 
(list 1354.585 114.4114) 
(list 1354.585 114.5884) 
(list 1280.5625 114.2384)))
(apply 'command (append '("pline") coords '("c")))
(setq currobj (ssadd (entlast) currobj))
(setq coords (list 
(list 1280.5625 114.3814) 
(list 1354.585 114.7314) 
(list 1354.585 114.9084) 
(list 1280.5625 114.4584)))
(apply 'command (append '("pline") coords '("c")))
(setq currobj (ssadd (entlast) currobj))
(setq coords (list 
(list 1280.5625 114.6014) 
(list 1354.585 115.0514) 
(list 1354.585 115.2284) 
(list 1280.5625 114.6784)))
(apply 'command (append '("pline") coords '("c")))
(setq currobj (ssadd (entlast) currobj))
(setq coords (list 
(list 1280.5625 114.8214) 
(list 1354.585 115.3714) 
(list 1354.585 115.5484) 
(list 1280.5625 114.8984)))
(apply 'command (append '("pline") coords '("c")))
(setq currobj (ssadd (entlast) currobj))
(setq coords (list 
(list 1280.5625 115.0414) 
(list 1354.585 115.6914) 
(list 1354.585 115.8684) 
(list 1280.5625 115.1184)))
(apply 'command (append '("pline") coords '("c")))
(setq currobj (ssadd (entlast) currobj))
(setq coords (list 
(list 1279.4375 115.1184) 
(list 1205.415 115.8684) 
(list 1205.415 115.6914) 
(list 1279.4375 115.0414)))
(apply 'command (append '("pline") coords '("c")))
(setq currobj (ssadd (entlast) currobj))
(setq coords (list 
(list 1279.4375 114.8984) 
(list 1205.415 115.5484) 
(list 1205.415 115.3714) 
(list 1279.4375 114.8214)))
(apply 'command (append '("pline") coords '("c")))
(setq currobj (ssadd (entlast) currobj))
(setq coords (list 
(list 1279.4375 114.6784) 
(list 1205.415 115.2284) 
(list 1205.415 115.0514) 
(list 1279.4375 114.6014)))
(apply 'command (append '("pline") coords '("c")))
(setq currobj (ssadd (entlast) currobj))
(setq coords (list 
(list 1279.4375 114.4584) 
(list 1205.415 114.9084) 
(list 1205.415 114.7314) 
(list 1279.4375 114.3814)))
(apply 'command (append '("pline") coords '("c")))
(setq currobj (ssadd (entlast) currobj))
(setq coords (list 
(list 1279.4375 114.2384) 
(list 1205.415 114.5884) 
(list 1205.415 114.4114) 
(list 1279.4375 114.1614)))
(apply 'command (append '("pline") coords '("c")))
(setq currobj (ssadd (entlast) currobj))
(setq coords (list 
(list 1279.4375 114.0184) 
(list 1205.415 114.2684) 
(list 1205.415 114.0914) 
(list 1279.4375 113.9414)))
(apply 'command (append '("pline") coords '("c")))
(setq currobj (ssadd (entlast) currobj))
(setq coords (list 
(list 1279.4375 113.7984) 
(list 1205.415 113.9484) 
(list 1205.415 113.7714) 
(list 1279.4375 113.7214)))
(apply 'command (append '("pline") coords '("c")))
(setq currobj (ssadd (entlast) currobj))
(setq coords (list 
(list 1279.4375 113.5784) 
(list 1205.415 113.6284) 
(list 1205.415 113.4514) 
(list 1279.4375 113.5014)))
(apply 'command (append '("pline") coords '("c")))
(setq currobj (ssadd (entlast) currobj))
(setq coords (list 
(list 1279.4375 113.3584) 
(list 1205.415 113.3084) 
(list 1205.415 113.1314) 
(list 1279.4375 113.2814)))
(apply 'command (append '("pline") coords '("c")))
(setq currobj (ssadd (entlast) currobj))
(setq coords (list 
(list 1279.4375 113.1384) 
(list 1205.415 112.9884) 
(list 1205.415 112.8114) 
(list 1279.4375 113.0614)))
(apply 'command (append '("pline") coords '("c")))
(setq currobj (ssadd (entlast) currobj))
(setq coords (list 
(list 1279.4375 112.9184) 
(list 1205.415 112.6684) 
(list 1205.415 112.4914) 
(list 1279.4375 112.8414)))
(apply 'command (append '("pline") coords '("c")))
(setq currobj (ssadd (entlast) currobj))
(setq coords (list 
(list 1279.4375 112.6984) 
(list 1205.415 112.3484) 
(list 1205.415 112.1714) 
(list 1279.4375 112.6214)))
(apply 'command (append '("pline") coords '("c")))
(setq currobj (ssadd (entlast) currobj))
(setq coords (list 
(list 1279.4375 112.4784) 
(list 1205.415 112.0284) 
(list 1205.415 111.8514) 
(list 1279.4375 112.4014)))
(apply 'command (append '("pline") coords '("c")))
(setq currobj (ssadd (entlast) currobj))
(setq coords (list 
(list 1279.4375 112.2584) 
(list 1205.415 111.7084) 
(list 1205.415 111.5314) 
(list 1279.4375 112.1814)))
(apply 'command (append '("pline") coords '("c")))
(setq currobj (ssadd (entlast) currobj))
(setq coords (list 
(list 1279.4375 112.0384) 
(list 1205.415 111.3884) 
(list 1205.415 111.2114) 
(list 1279.4375 111.9614)))
(apply 'command (append '("pline") coords '("c")))
(setq currobj (ssadd (entlast) currobj))
(command "_layer" "set" "nitride" "")
(command "_layer" "set" "text" "")
(command "_circle" "1279.0625,100.8184" "0.075")
(command "_circle" "1279.0625,101.1184" "0.075")
(command "_circle" "1279.0625,101.4184" "0.075")
(command "_circle" "1279.0625,101.7184" "0.075")
(command "_circle" "1279.0625,102.0184" "0.075")
(command "_circle" "1278.7625,100.8184" "0.075")
(command "_circle" "1278.7625,101.1184" "0.075")
(command "_circle" "1278.7625,101.4184" "0.075")
(command "_circle" "1278.7625,101.7184" "0.075")
(command "_circle" "1278.7625,102.0184" "0.075")
(command "_circle" "1278.4625,100.8184" "0.075")
(command "_circle" "1278.4625,101.1184" "0.075")
(command "_circle" "1278.4625,101.4184" "0.075")
(command "_circle" "1278.4625,101.7184" "0.075")
(command "_circle" "1278.4625,102.0184" "0.075")
(command "_circle" "1278.1625,100.8184" "0.075")
(command "_circle" "1278.1625,101.1184" "0.075")
(command "_circle" "1278.1625,101.4184" "0.075")
(command "_circle" "1278.1625,101.7184" "0.075")
(command "_circle" "1278.1625,102.0184" "0.075")
(command "_circle" "1277.8625,100.8184" "0.075")
(command "_circle" "1277.8625,101.1184" "0.075")
(command "_circle" "1277.8625,101.4184" "0.075")
(command "_circle" "1277.8625,101.7184" "0.075")
(command "_circle" "1277.8625,102.0184" "0.075")
(command "_layer" "set" "nitride" "")
(setq coords (list 
(list 1280.2625 126.2614) 
(list 1280.2625 241.9061) 
(list 1279.7375 241.9061) 
(list 1279.7375 126.2614)))
(apply 'command (append '("pline") coords '("c")))
(setq currobj (ssadd (entlast) currobj))
(command "_layer" "set" "prebias" "")
(command "_rectangle" "1279.7375,126.2614" "1280.2625,241.9061")
(setq currobj (ssadd (entlast) currobj))
(command "_layer" "set" "nitride" "")
(setq coords (list 
(list 1280.2625 241.9061) 
(list 1280.5625 251.9061) 
(list 1280.5625 251.9061) 
(list 1280.5625 252.9061) 
(list 1354.585 252.1561) 
(list 1354.585 257.0991) 
(list 1280.5625 256.3491) 
(list 1280.5625 257.3491) 
(list 1280.5625 257.3491) 
(list 1280.2625 267.3491) 
(list 1279.7375 267.3491) 
(list 1279.4375 257.3491) 
(list 1279.4375 257.3491) 
(list 1279.4375 256.3491) 
(list 1205.415 257.0991) 
(list 1205.415 252.1561) 
(list 1279.4375 252.9061) 
(list 1279.4375 251.9061) 
(list 1279.4375 251.9061) 
(list 1279.7375 241.9061)))
(apply 'command (append '("pline") coords '("c")))
(setq currobj (ssadd (entlast) currobj))
(command "_layer" "set" "prebias" "")
(setq coords (list 
(list 1279.4375 241.9061) 
(list 1279.4375 252.9061) 
(list 1205.415 252.1561) 
(list 1205.415 257.0991) 
(list 1279.4375 256.3491) 
(list 1279.4375 267.3491) 
(list 1280.5625 267.3491) 
(list 1280.5625 256.3491) 
(list 1354.585 257.0991) 
(list 1354.585 252.1561) 
(list 1280.5625 252.9061) 
(list 1280.5625 241.9061)))
(apply 'command (append '("pline") coords '("c")))
(setq currobj (ssadd (entlast) currobj))
(command "_layer" "set" "nitride" "")
(command "_layer" "set" "fda1" "")
(setq coords (list 
(list 1280.5625 253.0491) 
(list 1354.585 252.2991) 
(list 1354.585 252.4761) 
(list 1280.5625 253.1261)))
(apply 'command (append '("pline") coords '("c")))
(setq currobj (ssadd (entlast) currobj))
(setq coords (list 
(list 1280.5625 253.2691) 
(list 1354.585 252.6191) 
(list 1354.585 252.7961) 
(list 1280.5625 253.3461)))
(apply 'command (append '("pline") coords '("c")))
(setq currobj (ssadd (entlast) currobj))
(setq coords (list 
(list 1280.5625 253.4891) 
(list 1354.585 252.9391) 
(list 1354.585 253.1161) 
(list 1280.5625 253.5661)))
(apply 'command (append '("pline") coords '("c")))
(setq currobj (ssadd (entlast) currobj))
(setq coords (list 
(list 1280.5625 253.7091) 
(list 1354.585 253.2591) 
(list 1354.585 253.4361) 
(list 1280.5625 253.7861)))
(apply 'command (append '("pline") coords '("c")))
(setq currobj (ssadd (entlast) currobj))
(setq coords (list 
(list 1280.5625 253.9291) 
(list 1354.585 253.5791) 
(list 1354.585 253.7561) 
(list 1280.5625 254.0061)))
(apply 'command (append '("pline") coords '("c")))
(setq currobj (ssadd (entlast) currobj))
(setq coords (list 
(list 1280.5625 254.1491) 
(list 1354.585 253.8991) 
(list 1354.585 254.0761) 
(list 1280.5625 254.2261)))
(apply 'command (append '("pline") coords '("c")))
(setq currobj (ssadd (entlast) currobj))
(setq coords (list 
(list 1280.5625 254.3691) 
(list 1354.585 254.2191) 
(list 1354.585 254.3961) 
(list 1280.5625 254.4461)))
(apply 'command (append '("pline") coords '("c")))
(setq currobj (ssadd (entlast) currobj))
(setq coords (list 
(list 1280.5625 254.5891) 
(list 1354.585 254.5391) 
(list 1354.585 254.7161) 
(list 1280.5625 254.6661)))
(apply 'command (append '("pline") coords '("c")))
(setq currobj (ssadd (entlast) currobj))
(setq coords (list 
(list 1280.5625 254.8091) 
(list 1354.585 254.8591) 
(list 1354.585 255.0361) 
(list 1280.5625 254.8861)))
(apply 'command (append '("pline") coords '("c")))
(setq currobj (ssadd (entlast) currobj))
(setq coords (list 
(list 1280.5625 255.0291) 
(list 1354.585 255.1791) 
(list 1354.585 255.3561) 
(list 1280.5625 255.1061)))
(apply 'command (append '("pline") coords '("c")))
(setq currobj (ssadd (entlast) currobj))
(setq coords (list 
(list 1280.5625 255.2491) 
(list 1354.585 255.4991) 
(list 1354.585 255.6761) 
(list 1280.5625 255.3261)))
(apply 'command (append '("pline") coords '("c")))
(setq currobj (ssadd (entlast) currobj))
(setq coords (list 
(list 1280.5625 255.4691) 
(list 1354.585 255.8191) 
(list 1354.585 255.9961) 
(list 1280.5625 255.5461)))
(apply 'command (append '("pline") coords '("c")))
(setq currobj (ssadd (entlast) currobj))
(setq coords (list 
(list 1280.5625 255.6891) 
(list 1354.585 256.1391) 
(list 1354.585 256.3161) 
(list 1280.5625 255.7661)))
(apply 'command (append '("pline") coords '("c")))
(setq currobj (ssadd (entlast) currobj))
(setq coords (list 
(list 1280.5625 255.9091) 
(list 1354.585 256.4591) 
(list 1354.585 256.6361) 
(list 1280.5625 255.9861)))
(apply 'command (append '("pline") coords '("c")))
(setq currobj (ssadd (entlast) currobj))
(setq coords (list 
(list 1280.5625 256.1291) 
(list 1354.585 256.7791) 
(list 1354.585 256.9561) 
(list 1280.5625 256.2061)))
(apply 'command (append '("pline") coords '("c")))
(setq currobj (ssadd (entlast) currobj))
(setq coords (list 
(list 1279.4375 256.2061) 
(list 1205.415 256.9561) 
(list 1205.415 256.7791) 
(list 1279.4375 256.1291)))
(apply 'command (append '("pline") coords '("c")))
(setq currobj (ssadd (entlast) currobj))
(setq coords (list 
(list 1279.4375 255.9861) 
(list 1205.415 256.6361) 
(list 1205.415 256.4591) 
(list 1279.4375 255.9091)))
(apply 'command (append '("pline") coords '("c")))
(setq currobj (ssadd (entlast) currobj))
(setq coords (list 
(list 1279.4375 255.7661) 
(list 1205.415 256.3161) 
(list 1205.415 256.1391) 
(list 1279.4375 255.6891)))
(apply 'command (append '("pline") coords '("c")))
(setq currobj (ssadd (entlast) currobj))
(setq coords (list 
(list 1279.4375 255.5461) 
(list 1205.415 255.9961) 
(list 1205.415 255.8191) 
(list 1279.4375 255.4691)))
(apply 'command (append '("pline") coords '("c")))
(setq currobj (ssadd (entlast) currobj))
(setq coords (list 
(list 1279.4375 255.3261) 
(list 1205.415 255.6761) 
(list 1205.415 255.4991) 
(list 1279.4375 255.2491)))
(apply 'command (append '("pline") coords '("c")))
(setq currobj (ssadd (entlast) currobj))
(setq coords (list 
(list 1279.4375 255.1061) 
(list 1205.415 255.3561) 
(list 1205.415 255.1791) 
(list 1279.4375 255.0291)))
(apply 'command (append '("pline") coords '("c")))
(setq currobj (ssadd (entlast) currobj))
(setq coords (list 
(list 1279.4375 254.8861) 
(list 1205.415 255.0361) 
(list 1205.415 254.8591) 
(list 1279.4375 254.8091)))
(apply 'command (append '("pline") coords '("c")))
(setq currobj (ssadd (entlast) currobj))
(setq coords (list 
(list 1279.4375 254.6661) 
(list 1205.415 254.7161) 
(list 1205.415 254.5391) 
(list 1279.4375 254.5891)))
(apply 'command (append '("pline") coords '("c")))
(setq currobj (ssadd (entlast) currobj))
(setq coords (list 
(list 1279.4375 254.4461) 
(list 1205.415 254.3961) 
(list 1205.415 254.2191) 
(list 1279.4375 254.3691)))
(apply 'command (append '("pline") coords '("c")))
(setq currobj (ssadd (entlast) currobj))
(setq coords (list 
(list 1279.4375 254.2261) 
(list 1205.415 254.0761) 
(list 1205.415 253.8991) 
(list 1279.4375 254.1491)))
(apply 'command (append '("pline") coords '("c")))
(setq currobj (ssadd (entlast) currobj))
(setq coords (list 
(list 1279.4375 254.0061) 
(list 1205.415 253.7561) 
(list 1205.415 253.5791) 
(list 1279.4375 253.9291)))
(apply 'command (append '("pline") coords '("c")))
(setq currobj (ssadd (entlast) currobj))
(setq coords (list 
(list 1279.4375 253.7861) 
(list 1205.415 253.4361) 
(list 1205.415 253.2591) 
(list 1279.4375 253.7091)))
(apply 'command (append '("pline") coords '("c")))
(setq currobj (ssadd (entlast) currobj))
(setq coords (list 
(list 1279.4375 253.5661) 
(list 1205.415 253.1161) 
(list 1205.415 252.9391) 
(list 1279.4375 253.4891)))
(apply 'command (append '("pline") coords '("c")))
(setq currobj (ssadd (entlast) currobj))
(setq coords (list 
(list 1279.4375 253.3461) 
(list 1205.415 252.7961) 
(list 1205.415 252.6191) 
(list 1279.4375 253.2691)))
(apply 'command (append '("pline") coords '("c")))
(setq currobj (ssadd (entlast) currobj))
(setq coords (list 
(list 1279.4375 253.1261) 
(list 1205.415 252.4761) 
(list 1205.415 252.2991) 
(list 1279.4375 253.0491)))
(apply 'command (append '("pline") coords '("c")))
(setq currobj (ssadd (entlast) currobj))
(command "_layer" "set" "nitride" "")
(command "_layer" "set" "text" "")
(command "_circle" "1279.0625,241.9061" "0.075")
(command "_circle" "1279.0625,242.2061" "0.075")
(command "_circle" "1279.0625,242.5061" "0.075")
(command "_circle" "1279.0625,242.8061" "0.075")
(command "_circle" "1279.0625,243.1061" "0.075")
(command "_circle" "1278.7625,241.9061" "0.075")
(command "_circle" "1278.7625,242.2061" "0.075")
(command "_circle" "1278.7625,242.5061" "0.075")
(command "_circle" "1278.7625,242.8061" "0.075")
(command "_circle" "1278.7625,243.1061" "0.075")
(command "_circle" "1278.4625,241.9061" "0.075")
(command "_circle" "1278.4625,242.2061" "0.075")
(command "_circle" "1278.4625,242.5061" "0.075")
(command "_circle" "1278.4625,242.8061" "0.075")
(command "_circle" "1278.4625,243.1061" "0.075")
(command "_circle" "1278.1625,241.9061" "0.075")
(command "_circle" "1278.1625,242.2061" "0.075")
(command "_circle" "1278.1625,242.5061" "0.075")
(command "_circle" "1278.1625,242.8061" "0.075")
(command "_circle" "1278.1625,243.1061" "0.075")
(command "_circle" "1277.8625,241.9061" "0.075")
(command "_circle" "1277.8625,242.2061" "0.075")
(command "_circle" "1277.8625,242.5061" "0.075")
(command "_circle" "1277.8625,242.8061" "0.075")
(command "_circle" "1277.8625,243.1061" "0.075")
(command "_layer" "set" "nitride" "")
(setq coords (list 
(list 1280.2625 267.3491) 
(list 1280.2625 382.9939) 
(list 1279.7375 382.9939) 
(list 1279.7375 267.3491)))
(apply 'command (append '("pline") coords '("c")))
(setq currobj (ssadd (entlast) currobj))
(command "_layer" "set" "prebias" "")
(command "_rectangle" "1279.7375,267.3491" "1280.2625,382.9939")
(setq currobj (ssadd (entlast) currobj))
(command "_layer" "set" "nitride" "")
(setq coords (list 
(list 1280.2625 382.9939) 
(list 1280.5625 392.9939) 
(list 1280.5625 392.9939) 
(list 1280.5625 393.9939) 
(list 1354.585 393.2439) 
(list 1354.585 398.1869) 
(list 1280.5625 397.4369) 
(list 1280.5625 398.4369) 
(list 1280.5625 398.4369) 
(list 1280.2625 408.4369) 
(list 1279.7375 408.4369) 
(list 1279.4375 398.4369) 
(list 1279.4375 398.4369) 
(list 1279.4375 397.4369) 
(list 1205.415 398.1869) 
(list 1205.415 393.2439) 
(list 1279.4375 393.9939) 
(list 1279.4375 392.9939) 
(list 1279.4375 392.9939) 
(list 1279.7375 382.9939)))
(apply 'command (append '("pline") coords '("c")))
(setq currobj (ssadd (entlast) currobj))
(command "_layer" "set" "prebias" "")
(setq coords (list 
(list 1279.4375 382.9939) 
(list 1279.4375 393.9939) 
(list 1205.415 393.2439) 
(list 1205.415 398.1869) 
(list 1279.4375 397.4369) 
(list 1279.4375 408.4369) 
(list 1280.5625 408.4369) 
(list 1280.5625 397.4369) 
(list 1354.585 398.1869) 
(list 1354.585 393.2439) 
(list 1280.5625 393.9939) 
(list 1280.5625 382.9939)))
(apply 'command (append '("pline") coords '("c")))
(setq currobj (ssadd (entlast) currobj))
(command "_layer" "set" "nitride" "")
(command "_layer" "set" "fda1" "")
(setq coords (list 
(list 1280.5625 394.1369) 
(list 1354.585 393.3869) 
(list 1354.585 393.5639) 
(list 1280.5625 394.2139)))
(apply 'command (append '("pline") coords '("c")))
(setq currobj (ssadd (entlast) currobj))
(setq coords (list 
(list 1280.5625 394.3569) 
(list 1354.585 393.7069) 
(list 1354.585 393.8839) 
(list 1280.5625 394.4339)))
(apply 'command (append '("pline") coords '("c")))
(setq currobj (ssadd (entlast) currobj))
(setq coords (list 
(list 1280.5625 394.5769) 
(list 1354.585 394.0269) 
(list 1354.585 394.2039) 
(list 1280.5625 394.6539)))
(apply 'command (append '("pline") coords '("c")))
(setq currobj (ssadd (entlast) currobj))
(setq coords (list 
(list 1280.5625 394.7969) 
(list 1354.585 394.3469) 
(list 1354.585 394.5239) 
(list 1280.5625 394.8739)))
(apply 'command (append '("pline") coords '("c")))
(setq currobj (ssadd (entlast) currobj))
(setq coords (list 
(list 1280.5625 395.0169) 
(list 1354.585 394.6669) 
(list 1354.585 394.8439) 
(list 1280.5625 395.0939)))
(apply 'command (append '("pline") coords '("c")))
(setq currobj (ssadd (entlast) currobj))
(setq coords (list 
(list 1280.5625 395.2369) 
(list 1354.585 394.9869) 
(list 1354.585 395.1639) 
(list 1280.5625 395.3139)))
(apply 'command (append '("pline") coords '("c")))
(setq currobj (ssadd (entlast) currobj))
(setq coords (list 
(list 1280.5625 395.4569) 
(list 1354.585 395.3069) 
(list 1354.585 395.4839) 
(list 1280.5625 395.5339)))
(apply 'command (append '("pline") coords '("c")))
(setq currobj (ssadd (entlast) currobj))
(setq coords (list 
(list 1280.5625 395.6769) 
(list 1354.585 395.6269) 
(list 1354.585 395.8039) 
(list 1280.5625 395.7539)))
(apply 'command (append '("pline") coords '("c")))
(setq currobj (ssadd (entlast) currobj))
(setq coords (list 
(list 1280.5625 395.8969) 
(list 1354.585 395.9469) 
(list 1354.585 396.1239) 
(list 1280.5625 395.9739)))
(apply 'command (append '("pline") coords '("c")))
(setq currobj (ssadd (entlast) currobj))
(setq coords (list 
(list 1280.5625 396.1169) 
(list 1354.585 396.2669) 
(list 1354.585 396.4439) 
(list 1280.5625 396.1939)))
(apply 'command (append '("pline") coords '("c")))
(setq currobj (ssadd (entlast) currobj))
(setq coords (list 
(list 1280.5625 396.3369) 
(list 1354.585 396.5869) 
(list 1354.585 396.7639) 
(list 1280.5625 396.4139)))
(apply 'command (append '("pline") coords '("c")))
(setq currobj (ssadd (entlast) currobj))
(setq coords (list 
(list 1280.5625 396.5569) 
(list 1354.585 396.9069) 
(list 1354.585 397.0839) 
(list 1280.5625 396.6339)))
(apply 'command (append '("pline") coords '("c")))
(setq currobj (ssadd (entlast) currobj))
(setq coords (list 
(list 1280.5625 396.7769) 
(list 1354.585 397.2269) 
(list 1354.585 397.4039) 
(list 1280.5625 396.8539)))
(apply 'command (append '("pline") coords '("c")))
(setq currobj (ssadd (entlast) currobj))
(setq coords (list 
(list 1280.5625 396.9969) 
(list 1354.585 397.5469) 
(list 1354.585 397.7239) 
(list 1280.5625 397.0739)))
(apply 'command (append '("pline") coords '("c")))
(setq currobj (ssadd (entlast) currobj))
(setq coords (list 
(list 1280.5625 397.2169) 
(list 1354.585 397.8669) 
(list 1354.585 398.0439) 
(list 1280.5625 397.2939)))
(apply 'command (append '("pline") coords '("c")))
(setq currobj (ssadd (entlast) currobj))
(setq coords (list 
(list 1279.4375 397.2939) 
(list 1205.415 398.0439) 
(list 1205.415 397.8669) 
(list 1279.4375 397.2169)))
(apply 'command (append '("pline") coords '("c")))
(setq currobj (ssadd (entlast) currobj))
(setq coords (list 
(list 1279.4375 397.0739) 
(list 1205.415 397.7239) 
(list 1205.415 397.5469) 
(list 1279.4375 396.9969)))
(apply 'command (append '("pline") coords '("c")))
(setq currobj (ssadd (entlast) currobj))
(setq coords (list 
(list 1279.4375 396.8539) 
(list 1205.415 397.4039) 
(list 1205.415 397.2269) 
(list 1279.4375 396.7769)))
(apply 'command (append '("pline") coords '("c")))
(setq currobj (ssadd (entlast) currobj))
(setq coords (list 
(list 1279.4375 396.6339) 
(list 1205.415 397.0839) 
(list 1205.415 396.9069) 
(list 1279.4375 396.5569)))
(apply 'command (append '("pline") coords '("c")))
(setq currobj (ssadd (entlast) currobj))
(setq coords (list 
(list 1279.4375 396.4139) 
(list 1205.415 396.7639) 
(list 1205.415 396.5869) 
(list 1279.4375 396.3369)))
(apply 'command (append '("pline") coords '("c")))
(setq currobj (ssadd (entlast) currobj))
(setq coords (list 
(list 1279.4375 396.1939) 
(list 1205.415 396.4439) 
(list 1205.415 396.2669) 
(list 1279.4375 396.1169)))
(apply 'command (append '("pline") coords '("c")))
(setq currobj (ssadd (entlast) currobj))
(setq coords (list 
(list 1279.4375 395.9739) 
(list 1205.415 396.1239) 
(list 1205.415 395.9469) 
(list 1279.4375 395.8969)))
(apply 'command (append '("pline") coords '("c")))
(setq currobj (ssadd (entlast) currobj))
(setq coords (list 
(list 1279.4375 395.7539) 
(list 1205.415 395.8039) 
(list 1205.415 395.6269) 
(list 1279.4375 395.6769)))
(apply 'command (append '("pline") coords '("c")))
(setq currobj (ssadd (entlast) currobj))
(setq coords (list 
(list 1279.4375 395.5339) 
(list 1205.415 395.4839) 
(list 1205.415 395.3069) 
(list 1279.4375 395.4569)))
(apply 'command (append '("pline") coords '("c")))
(setq currobj (ssadd (entlast) currobj))
(setq coords (list 
(list 1279.4375 395.3139) 
(list 1205.415 395.1639) 
(list 1205.415 394.9869) 
(list 1279.4375 395.2369)))
(apply 'command (append '("pline") coords '("c")))
(setq currobj (ssadd (entlast) currobj))
(setq coords (list 
(list 1279.4375 395.0939) 
(list 1205.415 394.8439) 
(list 1205.415 394.6669) 
(list 1279.4375 395.0169)))
(apply 'command (append '("pline") coords '("c")))
(setq currobj (ssadd (entlast) currobj))
(setq coords (list 
(list 1279.4375 394.8739) 
(list 1205.415 394.5239) 
(list 1205.415 394.3469) 
(list 1279.4375 394.7969)))
(apply 'command (append '("pline") coords '("c")))
(setq currobj (ssadd (entlast) currobj))
(setq coords (list 
(list 1279.4375 394.6539) 
(list 1205.415 394.2039) 
(list 1205.415 394.0269) 
(list 1279.4375 394.5769)))
(apply 'command (append '("pline") coords '("c")))
(setq currobj (ssadd (entlast) currobj))
(setq coords (list 
(list 1279.4375 394.4339) 
(list 1205.415 393.8839) 
(list 1205.415 393.7069) 
(list 1279.4375 394.3569)))
(apply 'command (append '("pline") coords '("c")))
(setq currobj (ssadd (entlast) currobj))
(setq coords (list 
(list 1279.4375 394.2139) 
(list 1205.415 393.5639) 
(list 1205.415 393.3869) 
(list 1279.4375 394.1369)))
(apply 'command (append '("pline") coords '("c")))
(setq currobj (ssadd (entlast) currobj))
(command "_layer" "set" "nitride" "")
(command "_layer" "set" "text" "")
(command "_circle" "1279.0625,382.9939" "0.075")
(command "_circle" "1279.0625,383.2939" "0.075")
(command "_circle" "1279.0625,383.5939" "0.075")
(command "_circle" "1279.0625,383.8939" "0.075")
(command "_circle" "1279.0625,384.1939" "0.075")
(command "_circle" "1278.7625,382.9939" "0.075")
(command "_circle" "1278.7625,383.2939" "0.075")
(command "_circle" "1278.7625,383.5939" "0.075")
(command "_circle" "1278.7625,383.8939" "0.075")
(command "_circle" "1278.7625,384.1939" "0.075")
(command "_circle" "1278.4625,382.9939" "0.075")
(command "_circle" "1278.4625,383.2939" "0.075")
(command "_circle" "1278.4625,383.5939" "0.075")
(command "_circle" "1278.4625,383.8939" "0.075")
(command "_circle" "1278.4625,384.1939" "0.075")
(command "_circle" "1278.1625,382.9939" "0.075")
(command "_circle" "1278.1625,383.2939" "0.075")
(command "_circle" "1278.1625,383.5939" "0.075")
(command "_circle" "1278.1625,383.8939" "0.075")
(command "_circle" "1278.1625,384.1939" "0.075")
(command "_circle" "1277.8625,382.9939" "0.075")
(command "_circle" "1277.8625,383.2939" "0.075")
(command "_circle" "1277.8625,383.5939" "0.075")
(command "_circle" "1277.8625,383.8939" "0.075")
(command "_circle" "1277.8625,384.1939" "0.075")
(command "_layer" "set" "nitride" "")
(setq coords (list 
(list 1280.2625 408.4369) 
(list 1280.2625 524.0816) 
(list 1279.7375 524.0816) 
(list 1279.7375 408.4369)))
(apply 'command (append '("pline") coords '("c")))
(setq currobj (ssadd (entlast) currobj))
(command "_layer" "set" "prebias" "")
(command "_rectangle" "1279.7375,408.4369" "1280.2625,524.0816")
(setq currobj (ssadd (entlast) currobj))
(command "_layer" "set" "nitride" "")
(setq coords (list 
(list 1280.2625 524.0816) 
(list 1280.5625 534.0816) 
(list 1280.5625 534.0816) 
(list 1280.5625 535.0816) 
(list 1354.585 534.3316) 
(list 1354.585 539.2746) 
(list 1280.5625 538.5246) 
(list 1280.5625 539.5246) 
(list 1280.5625 539.5246) 
(list 1280.2625 549.5246) 
(list 1279.7375 549.5246) 
(list 1279.4375 539.5246) 
(list 1279.4375 539.5246) 
(list 1279.4375 538.5246) 
(list 1205.415 539.2746) 
(list 1205.415 534.3316) 
(list 1279.4375 535.0816) 
(list 1279.4375 534.0816) 
(list 1279.4375 534.0816) 
(list 1279.7375 524.0816)))
(apply 'command (append '("pline") coords '("c")))
(setq currobj (ssadd (entlast) currobj))
(command "_layer" "set" "prebias" "")
(setq coords (list 
(list 1279.4375 524.0816) 
(list 1279.4375 535.0816) 
(list 1205.415 534.3316) 
(list 1205.415 539.2746) 
(list 1279.4375 538.5246) 
(list 1279.4375 549.5246) 
(list 1280.5625 549.5246) 
(list 1280.5625 538.5246) 
(list 1354.585 539.2746) 
(list 1354.585 534.3316) 
(list 1280.5625 535.0816) 
(list 1280.5625 524.0816)))
(apply 'command (append '("pline") coords '("c")))
(setq currobj (ssadd (entlast) currobj))
(command "_layer" "set" "nitride" "")
(command "_layer" "set" "fda1" "")
(setq coords (list 
(list 1280.5625 535.2246) 
(list 1354.585 534.4746) 
(list 1354.585 534.6516) 
(list 1280.5625 535.3016)))
(apply 'command (append '("pline") coords '("c")))
(setq currobj (ssadd (entlast) currobj))
(setq coords (list 
(list 1280.5625 535.4446) 
(list 1354.585 534.7946) 
(list 1354.585 534.9716) 
(list 1280.5625 535.5216)))
(apply 'command (append '("pline") coords '("c")))
(setq currobj (ssadd (entlast) currobj))
(setq coords (list 
(list 1280.5625 535.6646) 
(list 1354.585 535.1146) 
(list 1354.585 535.2916) 
(list 1280.5625 535.7416)))
(apply 'command (append '("pline") coords '("c")))
(setq currobj (ssadd (entlast) currobj))
(setq coords (list 
(list 1280.5625 535.8846) 
(list 1354.585 535.4346) 
(list 1354.585 535.6116) 
(list 1280.5625 535.9616)))
(apply 'command (append '("pline") coords '("c")))
(setq currobj (ssadd (entlast) currobj))
(setq coords (list 
(list 1280.5625 536.1046) 
(list 1354.585 535.7546) 
(list 1354.585 535.9316) 
(list 1280.5625 536.1816)))
(apply 'command (append '("pline") coords '("c")))
(setq currobj (ssadd (entlast) currobj))
(setq coords (list 
(list 1280.5625 536.3246) 
(list 1354.585 536.0746) 
(list 1354.585 536.2516) 
(list 1280.5625 536.4016)))
(apply 'command (append '("pline") coords '("c")))
(setq currobj (ssadd (entlast) currobj))
(setq coords (list 
(list 1280.5625 536.5446) 
(list 1354.585 536.3946) 
(list 1354.585 536.5716) 
(list 1280.5625 536.6216)))
(apply 'command (append '("pline") coords '("c")))
(setq currobj (ssadd (entlast) currobj))
(setq coords (list 
(list 1280.5625 536.7646) 
(list 1354.585 536.7146) 
(list 1354.585 536.8916) 
(list 1280.5625 536.8416)))
(apply 'command (append '("pline") coords '("c")))
(setq currobj (ssadd (entlast) currobj))
(setq coords (list 
(list 1280.5625 536.9846) 
(list 1354.585 537.0346) 
(list 1354.585 537.2116) 
(list 1280.5625 537.0616)))
(apply 'command (append '("pline") coords '("c")))
(setq currobj (ssadd (entlast) currobj))
(setq coords (list 
(list 1280.5625 537.2046) 
(list 1354.585 537.3546) 
(list 1354.585 537.5316) 
(list 1280.5625 537.2816)))
(apply 'command (append '("pline") coords '("c")))
(setq currobj (ssadd (entlast) currobj))
(setq coords (list 
(list 1280.5625 537.4246) 
(list 1354.585 537.6746) 
(list 1354.585 537.8516) 
(list 1280.5625 537.5016)))
(apply 'command (append '("pline") coords '("c")))
(setq currobj (ssadd (entlast) currobj))
(setq coords (list 
(list 1280.5625 537.6446) 
(list 1354.585 537.9946) 
(list 1354.585 538.1716) 
(list 1280.5625 537.7216)))
(apply 'command (append '("pline") coords '("c")))
(setq currobj (ssadd (entlast) currobj))
(setq coords (list 
(list 1280.5625 537.8646) 
(list 1354.585 538.3146) 
(list 1354.585 538.4916) 
(list 1280.5625 537.9416)))
(apply 'command (append '("pline") coords '("c")))
(setq currobj (ssadd (entlast) currobj))
(setq coords (list 
(list 1280.5625 538.0846) 
(list 1354.585 538.6346) 
(list 1354.585 538.8116) 
(list 1280.5625 538.1616)))
(apply 'command (append '("pline") coords '("c")))
(setq currobj (ssadd (entlast) currobj))
(setq coords (list 
(list 1280.5625 538.3046) 
(list 1354.585 538.9546) 
(list 1354.585 539.1316) 
(list 1280.5625 538.3816)))
(apply 'command (append '("pline") coords '("c")))
(setq currobj (ssadd (entlast) currobj))
(setq coords (list 
(list 1279.4375 538.3816) 
(list 1205.415 539.1316) 
(list 1205.415 538.9546) 
(list 1279.4375 538.3046)))
(apply 'command (append '("pline") coords '("c")))
(setq currobj (ssadd (entlast) currobj))
(setq coords (list 
(list 1279.4375 538.1616) 
(list 1205.415 538.8116) 
(list 1205.415 538.6346) 
(list 1279.4375 538.0846)))
(apply 'command (append '("pline") coords '("c")))
(setq currobj (ssadd (entlast) currobj))
(setq coords (list 
(list 1279.4375 537.9416) 
(list 1205.415 538.4916) 
(list 1205.415 538.3146) 
(list 1279.4375 537.8646)))
(apply 'command (append '("pline") coords '("c")))
(setq currobj (ssadd (entlast) currobj))
(setq coords (list 
(list 1279.4375 537.7216) 
(list 1205.415 538.1716) 
(list 1205.415 537.9946) 
(list 1279.4375 537.6446)))
(apply 'command (append '("pline") coords '("c")))
(setq currobj (ssadd (entlast) currobj))
(setq coords (list 
(list 1279.4375 537.5016) 
(list 1205.415 537.8516) 
(list 1205.415 537.6746) 
(list 1279.4375 537.4246)))
(apply 'command (append '("pline") coords '("c")))
(setq currobj (ssadd (entlast) currobj))
(setq coords (list 
(list 1279.4375 537.2816) 
(list 1205.415 537.5316) 
(list 1205.415 537.3546) 
(list 1279.4375 537.2046)))
(apply 'command (append '("pline") coords '("c")))
(setq currobj (ssadd (entlast) currobj))
(setq coords (list 
(list 1279.4375 537.0616) 
(list 1205.415 537.2116) 
(list 1205.415 537.0346) 
(list 1279.4375 536.9846)))
(apply 'command (append '("pline") coords '("c")))
(setq currobj (ssadd (entlast) currobj))
(setq coords (list 
(list 1279.4375 536.8416) 
(list 1205.415 536.8916) 
(list 1205.415 536.7146) 
(list 1279.4375 536.7646)))
(apply 'command (append '("pline") coords '("c")))
(setq currobj (ssadd (entlast) currobj))
(setq coords (list 
(list 1279.4375 536.6216) 
(list 1205.415 536.5716) 
(list 1205.415 536.3946) 
(list 1279.4375 536.5446)))
(apply 'command (append '("pline") coords '("c")))
(setq currobj (ssadd (entlast) currobj))
(setq coords (list 
(list 1279.4375 536.4016) 
(list 1205.415 536.2516) 
(list 1205.415 536.0746) 
(list 1279.4375 536.3246)))
(apply 'command (append '("pline") coords '("c")))
(setq currobj (ssadd (entlast) currobj))
(setq coords (list 
(list 1279.4375 536.1816) 
(list 1205.415 535.9316) 
(list 1205.415 535.7546) 
(list 1279.4375 536.1046)))
(apply 'command (append '("pline") coords '("c")))
(setq currobj (ssadd (entlast) currobj))
(setq coords (list 
(list 1279.4375 535.9616) 
(list 1205.415 535.6116) 
(list 1205.415 535.4346) 
(list 1279.4375 535.8846)))
(apply 'command (append '("pline") coords '("c")))
(setq currobj (ssadd (entlast) currobj))
(setq coords (list 
(list 1279.4375 535.7416) 
(list 1205.415 535.2916) 
(list 1205.415 535.1146) 
(list 1279.4375 535.6646)))
(apply 'command (append '("pline") coords '("c")))
(setq currobj (ssadd (entlast) currobj))
(setq coords (list 
(list 1279.4375 535.5216) 
(list 1205.415 534.9716) 
(list 1205.415 534.7946) 
(list 1279.4375 535.4446)))
(apply 'command (append '("pline") coords '("c")))
(setq currobj (ssadd (entlast) currobj))
(setq coords (list 
(list 1279.4375 535.3016) 
(list 1205.415 534.6516) 
(list 1205.415 534.4746) 
(list 1279.4375 535.2246)))
(apply 'command (append '("pline") coords '("c")))
(setq currobj (ssadd (entlast) currobj))
(command "_layer" "set" "nitride" "")
(command "_layer" "set" "text" "")
(command "_circle" "1279.0625,524.0816" "0.075")
(command "_circle" "1279.0625,524.3816" "0.075")
(command "_circle" "1279.0625,524.6816" "0.075")
(command "_circle" "1279.0625,524.9816" "0.075")
(command "_circle" "1279.0625,525.2816" "0.075")
(command "_circle" "1278.7625,524.0816" "0.075")
(command "_circle" "1278.7625,524.3816" "0.075")
(command "_circle" "1278.7625,524.6816" "0.075")
(command "_circle" "1278.7625,524.9816" "0.075")
(command "_circle" "1278.7625,525.2816" "0.075")
(command "_circle" "1278.4625,524.0816" "0.075")
(command "_circle" "1278.4625,524.3816" "0.075")
(command "_circle" "1278.4625,524.6816" "0.075")
(command "_circle" "1278.4625,524.9816" "0.075")
(command "_circle" "1278.4625,525.2816" "0.075")
(command "_circle" "1278.1625,524.0816" "0.075")
(command "_circle" "1278.1625,524.3816" "0.075")
(command "_circle" "1278.1625,524.6816" "0.075")
(command "_circle" "1278.1625,524.9816" "0.075")
(command "_circle" "1278.1625,525.2816" "0.075")
(command "_circle" "1277.8625,524.0816" "0.075")
(command "_circle" "1277.8625,524.3816" "0.075")
(command "_circle" "1277.8625,524.6816" "0.075")
(command "_circle" "1277.8625,524.9816" "0.075")
(command "_circle" "1277.8625,525.2816" "0.075")
(command "_layer" "set" "nitride" "")
(setq coords (list 
(list 1280.2625 549.5246) 
(list 1280.2625 665.1693) 
(list 1279.7375 665.1693) 
(list 1279.7375 549.5246)))
(apply 'command (append '("pline") coords '("c")))
(setq currobj (ssadd (entlast) currobj))
(command "_layer" "set" "prebias" "")
(command "_rectangle" "1279.7375,549.5246" "1280.2625,665.1693")
(setq currobj (ssadd (entlast) currobj))
(command "_layer" "set" "nitride" "")
(setq coords (list 
(list 1280.2625 665.1693) 
(list 1280.5625 675.1693) 
(list 1280.5625 675.1693) 
(list 1280.5625 676.1693) 
(list 1354.585 675.4193) 
(list 1354.585 680.3623) 
(list 1280.5625 679.6123) 
(list 1280.5625 680.6123) 
(list 1280.5625 680.6123) 
(list 1280.2625 690.6123) 
(list 1279.7375 690.6123) 
(list 1279.4375 680.6123) 
(list 1279.4375 680.6123) 
(list 1279.4375 679.6123) 
(list 1205.415 680.3623) 
(list 1205.415 675.4193) 
(list 1279.4375 676.1693) 
(list 1279.4375 675.1693) 
(list 1279.4375 675.1693) 
(list 1279.7375 665.1693)))
(apply 'command (append '("pline") coords '("c")))
(setq currobj (ssadd (entlast) currobj))
(command "_layer" "set" "prebias" "")
(setq coords (list 
(list 1279.4375 665.1693) 
(list 1279.4375 676.1693) 
(list 1205.415 675.4193) 
(list 1205.415 680.3623) 
(list 1279.4375 679.6123) 
(list 1279.4375 690.6123) 
(list 1280.5625 690.6123) 
(list 1280.5625 679.6123) 
(list 1354.585 680.3623) 
(list 1354.585 675.4193) 
(list 1280.5625 676.1693) 
(list 1280.5625 665.1693)))
(apply 'command (append '("pline") coords '("c")))
(setq currobj (ssadd (entlast) currobj))
(command "_layer" "set" "nitride" "")
(command "_layer" "set" "fda1" "")
(setq coords (list 
(list 1280.5625 676.3123) 
(list 1354.585 675.5623) 
(list 1354.585 675.7393) 
(list 1280.5625 676.3893)))
(apply 'command (append '("pline") coords '("c")))
(setq currobj (ssadd (entlast) currobj))
(setq coords (list 
(list 1280.5625 676.5323) 
(list 1354.585 675.8823) 
(list 1354.585 676.0593) 
(list 1280.5625 676.6093)))
(apply 'command (append '("pline") coords '("c")))
(setq currobj (ssadd (entlast) currobj))
(setq coords (list 
(list 1280.5625 676.7523) 
(list 1354.585 676.2023) 
(list 1354.585 676.3793) 
(list 1280.5625 676.8293)))
(apply 'command (append '("pline") coords '("c")))
(setq currobj (ssadd (entlast) currobj))
(setq coords (list 
(list 1280.5625 676.9723) 
(list 1354.585 676.5223) 
(list 1354.585 676.6993) 
(list 1280.5625 677.0493)))
(apply 'command (append '("pline") coords '("c")))
(setq currobj (ssadd (entlast) currobj))
(setq coords (list 
(list 1280.5625 677.1923) 
(list 1354.585 676.8423) 
(list 1354.585 677.0193) 
(list 1280.5625 677.2693)))
(apply 'command (append '("pline") coords '("c")))
(setq currobj (ssadd (entlast) currobj))
(setq coords (list 
(list 1280.5625 677.4123) 
(list 1354.585 677.1623) 
(list 1354.585 677.3393) 
(list 1280.5625 677.4893)))
(apply 'command (append '("pline") coords '("c")))
(setq currobj (ssadd (entlast) currobj))
(setq coords (list 
(list 1280.5625 677.6323) 
(list 1354.585 677.4823) 
(list 1354.585 677.6593) 
(list 1280.5625 677.7093)))
(apply 'command (append '("pline") coords '("c")))
(setq currobj (ssadd (entlast) currobj))
(setq coords (list 
(list 1280.5625 677.8523) 
(list 1354.585 677.8023) 
(list 1354.585 677.9793) 
(list 1280.5625 677.9293)))
(apply 'command (append '("pline") coords '("c")))
(setq currobj (ssadd (entlast) currobj))
(setq coords (list 
(list 1280.5625 678.0723) 
(list 1354.585 678.1223) 
(list 1354.585 678.2993) 
(list 1280.5625 678.1493)))
(apply 'command (append '("pline") coords '("c")))
(setq currobj (ssadd (entlast) currobj))
(setq coords (list 
(list 1280.5625 678.2923) 
(list 1354.585 678.4423) 
(list 1354.585 678.6193) 
(list 1280.5625 678.3693)))
(apply 'command (append '("pline") coords '("c")))
(setq currobj (ssadd (entlast) currobj))
(setq coords (list 
(list 1280.5625 678.5123) 
(list 1354.585 678.7623) 
(list 1354.585 678.9393) 
(list 1280.5625 678.5893)))
(apply 'command (append '("pline") coords '("c")))
(setq currobj (ssadd (entlast) currobj))
(setq coords (list 
(list 1280.5625 678.7323) 
(list 1354.585 679.0823) 
(list 1354.585 679.2593) 
(list 1280.5625 678.8093)))
(apply 'command (append '("pline") coords '("c")))
(setq currobj (ssadd (entlast) currobj))
(setq coords (list 
(list 1280.5625 678.9523) 
(list 1354.585 679.4023) 
(list 1354.585 679.5793) 
(list 1280.5625 679.0293)))
(apply 'command (append '("pline") coords '("c")))
(setq currobj (ssadd (entlast) currobj))
(setq coords (list 
(list 1280.5625 679.1723) 
(list 1354.585 679.7223) 
(list 1354.585 679.8993) 
(list 1280.5625 679.2493)))
(apply 'command (append '("pline") coords '("c")))
(setq currobj (ssadd (entlast) currobj))
(setq coords (list 
(list 1280.5625 679.3923) 
(list 1354.585 680.0423) 
(list 1354.585 680.2193) 
(list 1280.5625 679.4693)))
(apply 'command (append '("pline") coords '("c")))
(setq currobj (ssadd (entlast) currobj))
(setq coords (list 
(list 1279.4375 679.4693) 
(list 1205.415 680.2193) 
(list 1205.415 680.0423) 
(list 1279.4375 679.3923)))
(apply 'command (append '("pline") coords '("c")))
(setq currobj (ssadd (entlast) currobj))
(setq coords (list 
(list 1279.4375 679.2493) 
(list 1205.415 679.8993) 
(list 1205.415 679.7223) 
(list 1279.4375 679.1723)))
(apply 'command (append '("pline") coords '("c")))
(setq currobj (ssadd (entlast) currobj))
(setq coords (list 
(list 1279.4375 679.0293) 
(list 1205.415 679.5793) 
(list 1205.415 679.4023) 
(list 1279.4375 678.9523)))
(apply 'command (append '("pline") coords '("c")))
(setq currobj (ssadd (entlast) currobj))
(setq coords (list 
(list 1279.4375 678.8093) 
(list 1205.415 679.2593) 
(list 1205.415 679.0823) 
(list 1279.4375 678.7323)))
(apply 'command (append '("pline") coords '("c")))
(setq currobj (ssadd (entlast) currobj))
(setq coords (list 
(list 1279.4375 678.5893) 
(list 1205.415 678.9393) 
(list 1205.415 678.7623) 
(list 1279.4375 678.5123)))
(apply 'command (append '("pline") coords '("c")))
(setq currobj (ssadd (entlast) currobj))
(setq coords (list 
(list 1279.4375 678.3693) 
(list 1205.415 678.6193) 
(list 1205.415 678.4423) 
(list 1279.4375 678.2923)))
(apply 'command (append '("pline") coords '("c")))
(setq currobj (ssadd (entlast) currobj))
(setq coords (list 
(list 1279.4375 678.1493) 
(list 1205.415 678.2993) 
(list 1205.415 678.1223) 
(list 1279.4375 678.0723)))
(apply 'command (append '("pline") coords '("c")))
(setq currobj (ssadd (entlast) currobj))
(setq coords (list 
(list 1279.4375 677.9293) 
(list 1205.415 677.9793) 
(list 1205.415 677.8023) 
(list 1279.4375 677.8523)))
(apply 'command (append '("pline") coords '("c")))
(setq currobj (ssadd (entlast) currobj))
(setq coords (list 
(list 1279.4375 677.7093) 
(list 1205.415 677.6593) 
(list 1205.415 677.4823) 
(list 1279.4375 677.6323)))
(apply 'command (append '("pline") coords '("c")))
(setq currobj (ssadd (entlast) currobj))
(setq coords (list 
(list 1279.4375 677.4893) 
(list 1205.415 677.3393) 
(list 1205.415 677.1623) 
(list 1279.4375 677.4123)))
(apply 'command (append '("pline") coords '("c")))
(setq currobj (ssadd (entlast) currobj))
(setq coords (list 
(list 1279.4375 677.2693) 
(list 1205.415 677.0193) 
(list 1205.415 676.8423) 
(list 1279.4375 677.1923)))
(apply 'command (append '("pline") coords '("c")))
(setq currobj (ssadd (entlast) currobj))
(setq coords (list 
(list 1279.4375 677.0493) 
(list 1205.415 676.6993) 
(list 1205.415 676.5223) 
(list 1279.4375 676.9723)))
(apply 'command (append '("pline") coords '("c")))
(setq currobj (ssadd (entlast) currobj))
(setq coords (list 
(list 1279.4375 676.8293) 
(list 1205.415 676.3793) 
(list 1205.415 676.2023) 
(list 1279.4375 676.7523)))
(apply 'command (append '("pline") coords '("c")))
(setq currobj (ssadd (entlast) currobj))
(setq coords (list 
(list 1279.4375 676.6093) 
(list 1205.415 676.0593) 
(list 1205.415 675.8823) 
(list 1279.4375 676.5323)))
(apply 'command (append '("pline") coords '("c")))
(setq currobj (ssadd (entlast) currobj))
(setq coords (list 
(list 1279.4375 676.3893) 
(list 1205.415 675.7393) 
(list 1205.415 675.5623) 
(list 1279.4375 676.3123)))
(apply 'command (append '("pline") coords '("c")))
(setq currobj (ssadd (entlast) currobj))
(command "_layer" "set" "nitride" "")
(command "_layer" "set" "text" "")
(command "_circle" "1279.0625,665.1693" "0.075")
(command "_circle" "1279.0625,665.4693" "0.075")
(command "_circle" "1279.0625,665.7693" "0.075")
(command "_circle" "1279.0625,666.0693" "0.075")
(command "_circle" "1279.0625,666.3693" "0.075")
(command "_circle" "1278.7625,665.1693" "0.075")
(command "_circle" "1278.7625,665.4693" "0.075")
(command "_circle" "1278.7625,665.7693" "0.075")
(command "_circle" "1278.7625,666.0693" "0.075")
(command "_circle" "1278.7625,666.3693" "0.075")
(command "_circle" "1278.4625,665.1693" "0.075")
(command "_circle" "1278.4625,665.4693" "0.075")
(command "_circle" "1278.4625,665.7693" "0.075")
(command "_circle" "1278.4625,666.0693" "0.075")
(command "_circle" "1278.4625,666.3693" "0.075")
(command "_circle" "1278.1625,665.1693" "0.075")
(command "_circle" "1278.1625,665.4693" "0.075")
(command "_circle" "1278.1625,665.7693" "0.075")
(command "_circle" "1278.1625,666.0693" "0.075")
(command "_circle" "1278.1625,666.3693" "0.075")
(command "_circle" "1277.8625,665.1693" "0.075")
(command "_circle" "1277.8625,665.4693" "0.075")
(command "_circle" "1277.8625,665.7693" "0.075")
(command "_circle" "1277.8625,666.0693" "0.075")
(command "_circle" "1277.8625,666.3693" "0.075")
(command "_layer" "set" "nitride" "")
(setq coords (list 
(list 1280.2625 690.6123) 
(list 1280.2625 806.257) 
(list 1279.7375 806.257) 
(list 1279.7375 690.6123)))
(apply 'command (append '("pline") coords '("c")))
(setq currobj (ssadd (entlast) currobj))
(command "_layer" "set" "prebias" "")
(command "_rectangle" "1279.7375,690.6123" "1280.2625,806.257")
(setq currobj (ssadd (entlast) currobj))
(command "_layer" "set" "nitride" "")
(setq coords (list 
(list 1280.2625 806.257) 
(list 1280.5625 816.257) 
(list 1280.5625 816.257) 
(list 1280.5625 817.257) 
(list 1354.585 816.507) 
(list 1354.585 821.45) 
(list 1280.5625 820.7) 
(list 1280.5625 821.7) 
(list 1280.5625 821.7) 
(list 1280.2625 831.7) 
(list 1279.7375 831.7) 
(list 1279.4375 821.7) 
(list 1279.4375 821.7) 
(list 1279.4375 820.7) 
(list 1205.415 821.45) 
(list 1205.415 816.507) 
(list 1279.4375 817.257) 
(list 1279.4375 816.257) 
(list 1279.4375 816.257) 
(list 1279.7375 806.257)))
(apply 'command (append '("pline") coords '("c")))
(setq currobj (ssadd (entlast) currobj))
(command "_layer" "set" "prebias" "")
(setq coords (list 
(list 1279.4375 806.257) 
(list 1279.4375 817.257) 
(list 1205.415 816.507) 
(list 1205.415 821.45) 
(list 1279.4375 820.7) 
(list 1279.4375 831.7) 
(list 1280.5625 831.7) 
(list 1280.5625 820.7) 
(list 1354.585 821.45) 
(list 1354.585 816.507) 
(list 1280.5625 817.257) 
(list 1280.5625 806.257)))
(apply 'command (append '("pline") coords '("c")))
(setq currobj (ssadd (entlast) currobj))
(command "_layer" "set" "nitride" "")
(command "_layer" "set" "fda1" "")
(setq coords (list 
(list 1280.5625 817.4) 
(list 1354.585 816.65) 
(list 1354.585 816.827) 
(list 1280.5625 817.477)))
(apply 'command (append '("pline") coords '("c")))
(setq currobj (ssadd (entlast) currobj))
(setq coords (list 
(list 1280.5625 817.62) 
(list 1354.585 816.97) 
(list 1354.585 817.147) 
(list 1280.5625 817.697)))
(apply 'command (append '("pline") coords '("c")))
(setq currobj (ssadd (entlast) currobj))
(setq coords (list 
(list 1280.5625 817.84) 
(list 1354.585 817.29) 
(list 1354.585 817.467) 
(list 1280.5625 817.917)))
(apply 'command (append '("pline") coords '("c")))
(setq currobj (ssadd (entlast) currobj))
(setq coords (list 
(list 1280.5625 818.06) 
(list 1354.585 817.61) 
(list 1354.585 817.787) 
(list 1280.5625 818.137)))
(apply 'command (append '("pline") coords '("c")))
(setq currobj (ssadd (entlast) currobj))
(setq coords (list 
(list 1280.5625 818.28) 
(list 1354.585 817.93) 
(list 1354.585 818.107) 
(list 1280.5625 818.357)))
(apply 'command (append '("pline") coords '("c")))
(setq currobj (ssadd (entlast) currobj))
(setq coords (list 
(list 1280.5625 818.5) 
(list 1354.585 818.25) 
(list 1354.585 818.427) 
(list 1280.5625 818.577)))
(apply 'command (append '("pline") coords '("c")))
(setq currobj (ssadd (entlast) currobj))
(setq coords (list 
(list 1280.5625 818.72) 
(list 1354.585 818.57) 
(list 1354.585 818.747) 
(list 1280.5625 818.797)))
(apply 'command (append '("pline") coords '("c")))
(setq currobj (ssadd (entlast) currobj))
(setq coords (list 
(list 1280.5625 818.94) 
(list 1354.585 818.89) 
(list 1354.585 819.067) 
(list 1280.5625 819.017)))
(apply 'command (append '("pline") coords '("c")))
(setq currobj (ssadd (entlast) currobj))
(setq coords (list 
(list 1280.5625 819.16) 
(list 1354.585 819.21) 
(list 1354.585 819.387) 
(list 1280.5625 819.237)))
(apply 'command (append '("pline") coords '("c")))
(setq currobj (ssadd (entlast) currobj))
(setq coords (list 
(list 1280.5625 819.38) 
(list 1354.585 819.53) 
(list 1354.585 819.707) 
(list 1280.5625 819.457)))
(apply 'command (append '("pline") coords '("c")))
(setq currobj (ssadd (entlast) currobj))
(setq coords (list 
(list 1280.5625 819.6) 
(list 1354.585 819.85) 
(list 1354.585 820.027) 
(list 1280.5625 819.677)))
(apply 'command (append '("pline") coords '("c")))
(setq currobj (ssadd (entlast) currobj))
(setq coords (list 
(list 1280.5625 819.82) 
(list 1354.585 820.17) 
(list 1354.585 820.347) 
(list 1280.5625 819.897)))
(apply 'command (append '("pline") coords '("c")))
(setq currobj (ssadd (entlast) currobj))
(setq coords (list 
(list 1280.5625 820.04) 
(list 1354.585 820.49) 
(list 1354.585 820.667) 
(list 1280.5625 820.117)))
(apply 'command (append '("pline") coords '("c")))
(setq currobj (ssadd (entlast) currobj))
(setq coords (list 
(list 1280.5625 820.26) 
(list 1354.585 820.81) 
(list 1354.585 820.987) 
(list 1280.5625 820.337)))
(apply 'command (append '("pline") coords '("c")))
(setq currobj (ssadd (entlast) currobj))
(setq coords (list 
(list 1280.5625 820.48) 
(list 1354.585 821.13) 
(list 1354.585 821.307) 
(list 1280.5625 820.557)))
(apply 'command (append '("pline") coords '("c")))
(setq currobj (ssadd (entlast) currobj))
(setq coords (list 
(list 1279.4375 820.557) 
(list 1205.415 821.307) 
(list 1205.415 821.13) 
(list 1279.4375 820.48)))
(apply 'command (append '("pline") coords '("c")))
(setq currobj (ssadd (entlast) currobj))
(setq coords (list 
(list 1279.4375 820.337) 
(list 1205.415 820.987) 
(list 1205.415 820.81) 
(list 1279.4375 820.26)))
(apply 'command (append '("pline") coords '("c")))
(setq currobj (ssadd (entlast) currobj))
(setq coords (list 
(list 1279.4375 820.117) 
(list 1205.415 820.667) 
(list 1205.415 820.49) 
(list 1279.4375 820.04)))
(apply 'command (append '("pline") coords '("c")))
(setq currobj (ssadd (entlast) currobj))
(setq coords (list 
(list 1279.4375 819.897) 
(list 1205.415 820.347) 
(list 1205.415 820.17) 
(list 1279.4375 819.82)))
(apply 'command (append '("pline") coords '("c")))
(setq currobj (ssadd (entlast) currobj))
(setq coords (list 
(list 1279.4375 819.677) 
(list 1205.415 820.027) 
(list 1205.415 819.85) 
(list 1279.4375 819.6)))
(apply 'command (append '("pline") coords '("c")))
(setq currobj (ssadd (entlast) currobj))
(setq coords (list 
(list 1279.4375 819.457) 
(list 1205.415 819.707) 
(list 1205.415 819.53) 
(list 1279.4375 819.38)))
(apply 'command (append '("pline") coords '("c")))
(setq currobj (ssadd (entlast) currobj))
(setq coords (list 
(list 1279.4375 819.237) 
(list 1205.415 819.387) 
(list 1205.415 819.21) 
(list 1279.4375 819.16)))
(apply 'command (append '("pline") coords '("c")))
(setq currobj (ssadd (entlast) currobj))
(setq coords (list 
(list 1279.4375 819.017) 
(list 1205.415 819.067) 
(list 1205.415 818.89) 
(list 1279.4375 818.94)))
(apply 'command (append '("pline") coords '("c")))
(setq currobj (ssadd (entlast) currobj))
(setq coords (list 
(list 1279.4375 818.797) 
(list 1205.415 818.747) 
(list 1205.415 818.57) 
(list 1279.4375 818.72)))
(apply 'command (append '("pline") coords '("c")))
(setq currobj (ssadd (entlast) currobj))
(setq coords (list 
(list 1279.4375 818.577) 
(list 1205.415 818.427) 
(list 1205.415 818.25) 
(list 1279.4375 818.5)))
(apply 'command (append '("pline") coords '("c")))
(setq currobj (ssadd (entlast) currobj))
(setq coords (list 
(list 1279.4375 818.357) 
(list 1205.415 818.107) 
(list 1205.415 817.93) 
(list 1279.4375 818.28)))
(apply 'command (append '("pline") coords '("c")))
(setq currobj (ssadd (entlast) currobj))
(setq coords (list 
(list 1279.4375 818.137) 
(list 1205.415 817.787) 
(list 1205.415 817.61) 
(list 1279.4375 818.06)))
(apply 'command (append '("pline") coords '("c")))
(setq currobj (ssadd (entlast) currobj))
(setq coords (list 
(list 1279.4375 817.917) 
(list 1205.415 817.467) 
(list 1205.415 817.29) 
(list 1279.4375 817.84)))
(apply 'command (append '("pline") coords '("c")))
(setq currobj (ssadd (entlast) currobj))
(setq coords (list 
(list 1279.4375 817.697) 
(list 1205.415 817.147) 
(list 1205.415 816.97) 
(list 1279.4375 817.62)))
(apply 'command (append '("pline") coords '("c")))
(setq currobj (ssadd (entlast) currobj))
(setq coords (list 
(list 1279.4375 817.477) 
(list 1205.415 816.827) 
(list 1205.415 816.65) 
(list 1279.4375 817.4)))
(apply 'command (append '("pline") coords '("c")))
(setq currobj (ssadd (entlast) currobj))
(command "_layer" "set" "nitride" "")
(command "_layer" "set" "text" "")
(command "_circle" "1279.0625,806.257" "0.075")
(command "_circle" "1279.0625,806.557" "0.075")
(command "_circle" "1279.0625,806.857" "0.075")
(command "_circle" "1279.0625,807.157" "0.075")
(command "_circle" "1279.0625,807.457" "0.075")
(command "_circle" "1278.7625,806.257" "0.075")
(command "_circle" "1278.7625,806.557" "0.075")
(command "_circle" "1278.7625,806.857" "0.075")
(command "_circle" "1278.7625,807.157" "0.075")
(command "_circle" "1278.7625,807.457" "0.075")
(command "_circle" "1278.4625,806.257" "0.075")
(command "_circle" "1278.4625,806.557" "0.075")
(command "_circle" "1278.4625,806.857" "0.075")
(command "_circle" "1278.4625,807.157" "0.075")
(command "_circle" "1278.4625,807.457" "0.075")
(command "_circle" "1278.1625,806.257" "0.075")
(command "_circle" "1278.1625,806.557" "0.075")
(command "_circle" "1278.1625,806.857" "0.075")
(command "_circle" "1278.1625,807.157" "0.075")
(command "_circle" "1278.1625,807.457" "0.075")
(command "_circle" "1277.8625,806.257" "0.075")
(command "_circle" "1277.8625,806.557" "0.075")
(command "_circle" "1277.8625,806.857" "0.075")
(command "_circle" "1277.8625,807.157" "0.075")
(command "_circle" "1277.8625,807.457" "0.075")
(command "_layer" "set" "nitride" "")
(setq coords (list 
(list 1280.2625 831.7) 
(list 1280.2625 836.7) 
(list 1279.7375 836.7) 
(list 1279.7375 831.7)))
(apply 'command (append '("pline") coords '("c")))
(setq currobj (ssadd (entlast) currobj))
(command "_layer" "set" "prebias" "")
(command "_rectangle" "1279.7375,831.7" "1280.2625,836.7")
(setq currobj (ssadd (entlast) currobj))
(command "_layer" "set" "nitride" "")
(setq cooledsinglenanobeam4 currobj)
(setq currobj nil)
(setq currobj (ssadd))
; DRAWING PHOTONIC CRYSTAL
(command "_layer" "set" "negYjunc" "")
(setq coords (list 
(list 1280.135 866.7) 
(list 1280 851.7) 
(list 1280 866.7)))
(apply 'command (append '("pline") coords '("c")))
(setq currobj (ssadd (entlast) currobj))
(setq coords (list 
(list 1280.2625 836.7) 
(list 1280.415 866.7) 
(list 1281.125 866.7) 
(list 1281.125 836.7)))
(apply 'command (append '("pline") coords '("c")))
(setq currobj (ssadd (entlast) currobj))
(setq coords (list 
(list 1279.865 866.7) 
(list 1280 851.7) 
(list 1280 866.7)))
(apply 'command (append '("pline") coords '("c")))
(setq currobj (ssadd (entlast) currobj))
(setq coords (list 
(list 1279.7375 836.7) 
(list 1279.585 866.7) 
(list 1278.875 866.7) 
(list 1278.875 836.7)))
(apply 'command (append '("pline") coords '("c")))
(setq currobj (ssadd (entlast) currobj))
(command "_layer" "set" "nitride" "")
(setq yjunction4 currobj)
(setq currobj nil)
(setq currobj (ssadd))
(setq tap4 nil)
(setq tap4 (ssadd))
(command "_layer" "set" "phc" "")
(setq coords (list 
(list 1280 866.7) 
(list 1280.135 866.7) 
(list 1280.135 866.7103) 
(list 1280.135 866.7206) 
(list 1280.135 866.7308) 
(list 1280.135 866.7411) 
(list 1280.135 866.7514) 
(list 1280.135 866.7617) 
(list 1280.135 866.7719) 
(list 1280.135 866.7822) 
(list 1280.135 866.7925) 
(list 1280.135 866.8028) 
(list 1280.135 866.8131) 
(list 1280.135 866.8233) 
(list 1280.135 866.8336) 
(list 1280.135 866.8439) 
(list 1280.135 866.8542) 
(list 1280.135 866.8644) 
(list 1280.135 866.8747) 
(list 1280.135 866.885) 
(list 1280.135 866.8953) 
(list 1280.135 866.9056) 
(list 1280.135 866.9158) 
(list 1280.135 866.9261) 
(list 1280.135 866.9364) 
(list 1280.135 866.9467) 
(list 1280.135 866.9569) 
(list 1280.135 866.9672) 
(list 1280.135 866.9775) 
(list 1280.135 866.9878) 
(list 1280.135 866.9981) 
(list 1280.135 867.0083) 
(list 1280.135 867.0186) 
(list 1280.135 867.0289) 
(list 1280.135 867.0392) 
(list 1280.135 867.0494) 
(list 1280.135 867.0597) 
(list 1280.135 867.07) 
(list 1280 867.07)))
(apply 'command (append '("pline") coords '("c")))
(setq tap4 (ssadd (entlast) tap4))
(command "_mirror" (entlast) "" "1280,900" "1280,901" "No")
(setq tap4 (ssadd (entlast) tap4))
(setq coords (list 
(list 1280.4248 866.7) 
(list 1280.415 866.7) 
(list 1280.4153 866.7103) 
(list 1280.4155 866.7206) 
(list 1280.4157 866.7308) 
(list 1280.4159 866.7411) 
(list 1280.4159 866.7514) 
(list 1280.4159 866.7617) 
(list 1280.4158 866.7719) 
(list 1280.4155 866.7822) 
(list 1280.4152 866.7925) 
(list 1280.4148 866.8028) 
(list 1280.4143 866.8131) 
(list 1280.4138 866.8233) 
(list 1280.4132 866.8336) 
(list 1280.4126 866.8439) 
(list 1280.4121 866.8542) 
(list 1280.4116 866.8644) 
(list 1280.4112 866.8747) 
(list 1280.4109 866.885) 
(list 1280.4107 866.8953) 
(list 1280.4107 866.9056) 
(list 1280.4109 866.9158) 
(list 1280.4113 866.9261) 
(list 1280.4118 866.9364) 
(list 1280.4125 866.9467) 
(list 1280.4134 866.9569) 
(list 1280.4144 866.9672) 
(list 1280.4156 866.9775) 
(list 1280.4168 866.9878) 
(list 1280.4181 866.9981) 
(list 1280.4194 867.0083) 
(list 1280.4207 867.0186) 
(list 1280.4219 867.0289) 
(list 1280.4229 867.0392) 
(list 1280.4238 867.0494) 
(list 1280.4244 867.0597) 
(list 1280.4248 867.07) 
(list 1280.4248 867.07)))
(apply 'command (append '("pline") coords '("c")))
(setq tap4 (ssadd (entlast) tap4))
(command "_mirror" (entlast) "" "1280,900" "1280,901" "No")
(setq tap4 (ssadd (entlast) tap4))
(setq coords (list 
(list 1281.125 866.7) 
(list 1280.4248 866.7) 
(list 1280.4248 866.7103) 
(list 1280.4248 866.7206) 
(list 1280.4248 866.7308) 
(list 1280.4248 866.7411) 
(list 1280.4248 866.7514) 
(list 1280.4248 866.7617) 
(list 1280.4248 866.7719) 
(list 1280.4248 866.7822) 
(list 1280.4248 866.7925) 
(list 1280.4248 866.8028) 
(list 1280.4248 866.8131) 
(list 1280.4248 866.8233) 
(list 1280.4248 866.8336) 
(list 1280.4248 866.8439) 
(list 1280.4248 866.8542) 
(list 1280.4248 866.8644) 
(list 1280.4248 866.8747) 
(list 1280.4248 866.885) 
(list 1280.4248 866.8953) 
(list 1280.4248 866.9056) 
(list 1280.4248 866.9158) 
(list 1280.4248 866.9261) 
(list 1280.4248 866.9364) 
(list 1280.4248 866.9467) 
(list 1280.4248 866.9569) 
(list 1280.4248 866.9672) 
(list 1280.4248 866.9775) 
(list 1280.4248 866.9878) 
(list 1280.4248 866.9981) 
(list 1280.4248 867.0083) 
(list 1280.4248 867.0186) 
(list 1280.4248 867.0289) 
(list 1280.4248 867.0392) 
(list 1280.4248 867.0494) 
(list 1280.4248 867.0597) 
(list 1280.4248 867.07) 
(list 1281.125 867.07)))
(apply 'command (append '("pline") coords '("c")))
(setq tap4 (ssadd (entlast) tap4))
(command "_mirror" (entlast) "" "1280,900" "1280,901" "No")
(setq tap4 (ssadd (entlast) tap4))
(setq coords (list 
(list 1280 867.07) 
(list 1280.135 867.07) 
(list 1280.135 867.0803) 
(list 1280.135 867.0906) 
(list 1280.135 867.1008) 
(list 1280.135 867.1111) 
(list 1280.135 867.1214) 
(list 1280.135 867.1317) 
(list 1280.135 867.1419) 
(list 1280.135 867.1522) 
(list 1280.135 867.1625) 
(list 1280.135 867.1728) 
(list 1280.135 867.1831) 
(list 1280.135 867.1933) 
(list 1280.135 867.2036) 
(list 1280.135 867.2139) 
(list 1280.135 867.2242) 
(list 1280.135 867.2344) 
(list 1280.135 867.2447) 
(list 1280.135 867.255) 
(list 1280.135 867.2653) 
(list 1280.135 867.2756) 
(list 1280.135 867.2858) 
(list 1280.135 867.2961) 
(list 1280.135 867.3064) 
(list 1280.135 867.3167) 
(list 1280.135 867.3269) 
(list 1280.135 867.3372) 
(list 1280.135 867.3475) 
(list 1280.135 867.3578) 
(list 1280.135 867.3681) 
(list 1280.135 867.3783) 
(list 1280.135 867.3886) 
(list 1280.135 867.3989) 
(list 1280.135 867.4092) 
(list 1280.135 867.4194) 
(list 1280.135 867.4297) 
(list 1280.135 867.44) 
(list 1280 867.44)))
(apply 'command (append '("pline") coords '("c")))
(setq tap4 (ssadd (entlast) tap4))
(command "_mirror" (entlast) "" "1280,900" "1280,901" "No")
(setq tap4 (ssadd (entlast) tap4))
(setq coords (list 
(list 1280.4347 867.07) 
(list 1280.4248 867.07) 
(list 1280.425 867.0803) 
(list 1280.4248 867.0906) 
(list 1280.4243 867.1008) 
(list 1280.4236 867.1111) 
(list 1280.4225 867.1214) 
(list 1280.4212 867.1317) 
(list 1280.4196 867.1419) 
(list 1280.4179 867.1522) 
(list 1280.416 867.1625) 
(list 1280.414 867.1728) 
(list 1280.412 867.1831) 
(list 1280.41 867.1933) 
(list 1280.4082 867.2036) 
(list 1280.4065 867.2139) 
(list 1280.4051 867.2242) 
(list 1280.4039 867.2344) 
(list 1280.4031 867.2447) 
(list 1280.4026 867.255) 
(list 1280.4026 867.2653) 
(list 1280.403 867.2756) 
(list 1280.4039 867.2858) 
(list 1280.4051 867.2961) 
(list 1280.4068 867.3064) 
(list 1280.4088 867.3167) 
(list 1280.4111 867.3269) 
(list 1280.4137 867.3372) 
(list 1280.4164 867.3475) 
(list 1280.4192 867.3578) 
(list 1280.422 867.3681) 
(list 1280.4247 867.3783) 
(list 1280.4273 867.3886) 
(list 1280.4296 867.3989) 
(list 1280.4315 867.4092) 
(list 1280.4331 867.4194) 
(list 1280.4341 867.4297) 
(list 1280.4347 867.44) 
(list 1280.4347 867.44)))
(apply 'command (append '("pline") coords '("c")))
(setq tap4 (ssadd (entlast) tap4))
(command "_mirror" (entlast) "" "1280,900" "1280,901" "No")
(setq tap4 (ssadd (entlast) tap4))
(setq coords (list 
(list 1281.125 867.07) 
(list 1280.4347 867.07) 
(list 1280.4347 867.0803) 
(list 1280.4347 867.0906) 
(list 1280.4347 867.1008) 
(list 1280.4347 867.1111) 
(list 1280.4347 867.1214) 
(list 1280.4347 867.1317) 
(list 1280.4347 867.1419) 
(list 1280.4347 867.1522) 
(list 1280.4347 867.1625) 
(list 1280.4347 867.1728) 
(list 1280.4347 867.1831) 
(list 1280.4347 867.1933) 
(list 1280.4347 867.2036) 
(list 1280.4347 867.2139) 
(list 1280.4347 867.2242) 
(list 1280.4347 867.2344) 
(list 1280.4347 867.2447) 
(list 1280.4347 867.255) 
(list 1280.4347 867.2653) 
(list 1280.4347 867.2756) 
(list 1280.4347 867.2858) 
(list 1280.4347 867.2961) 
(list 1280.4347 867.3064) 
(list 1280.4347 867.3167) 
(list 1280.4347 867.3269) 
(list 1280.4347 867.3372) 
(list 1280.4347 867.3475) 
(list 1280.4347 867.3578) 
(list 1280.4347 867.3681) 
(list 1280.4347 867.3783) 
(list 1280.4347 867.3886) 
(list 1280.4347 867.3989) 
(list 1280.4347 867.4092) 
(list 1280.4347 867.4194) 
(list 1280.4347 867.4297) 
(list 1280.4347 867.44) 
(list 1281.125 867.44)))
(apply 'command (append '("pline") coords '("c")))
(setq tap4 (ssadd (entlast) tap4))
(command "_mirror" (entlast) "" "1280,900" "1280,901" "No")
(setq tap4 (ssadd (entlast) tap4))
(setq coords (list 
(list 1280 867.44) 
(list 1280.135 867.44) 
(list 1280.135 867.4503) 
(list 1280.135 867.4606) 
(list 1280.135 867.4708) 
(list 1280.135 867.4811) 
(list 1280.135 867.4914) 
(list 1280.135 867.5017) 
(list 1280.135 867.5119) 
(list 1280.135 867.5222) 
(list 1280.135 867.5325) 
(list 1280.135 867.5428) 
(list 1280.135 867.5531) 
(list 1280.135 867.5633) 
(list 1280.135 867.5736) 
(list 1280.135 867.5839) 
(list 1280.135 867.5942) 
(list 1280.135 867.6044) 
(list 1280.135 867.6147) 
(list 1280.135 867.625) 
(list 1280.135 867.6353) 
(list 1280.135 867.6456) 
(list 1280.135 867.6558) 
(list 1280.135 867.6661) 
(list 1280.135 867.6764) 
(list 1280.135 867.6867) 
(list 1280.135 867.6969) 
(list 1280.135 867.7072) 
(list 1280.135 867.7175) 
(list 1280.135 867.7278) 
(list 1280.135 867.7381) 
(list 1280.135 867.7483) 
(list 1280.135 867.7586) 
(list 1280.135 867.7689) 
(list 1280.135 867.7792) 
(list 1280.135 867.7894) 
(list 1280.135 867.7997) 
(list 1280.135 867.81) 
(list 1280 867.81)))
(apply 'command (append '("pline") coords '("c")))
(setq tap4 (ssadd (entlast) tap4))
(command "_mirror" (entlast) "" "1280,900" "1280,901" "No")
(setq tap4 (ssadd (entlast) tap4))
(setq coords (list 
(list 1280.4445 867.44) 
(list 1280.4347 867.44) 
(list 1280.4347 867.4503) 
(list 1280.4341 867.4606) 
(list 1280.433 867.4708) 
(list 1280.4313 867.4811) 
(list 1280.4291 867.4914) 
(list 1280.4265 867.5017) 
(list 1280.4235 867.5119) 
(list 1280.4203 867.5222) 
(list 1280.4168 867.5325) 
(list 1280.4132 867.5428) 
(list 1280.4097 867.5531) 
(list 1280.4063 867.5633) 
(list 1280.4032 867.5736) 
(list 1280.4004 867.5839) 
(list 1280.398 867.5942) 
(list 1280.3962 867.6044) 
(list 1280.395 867.6147) 
(list 1280.3944 867.625) 
(list 1280.3945 867.6353) 
(list 1280.3954 867.6456) 
(list 1280.3969 867.6558) 
(list 1280.399 867.6661) 
(list 1280.4018 867.6764) 
(list 1280.4051 867.6867) 
(list 1280.4088 867.6969) 
(list 1280.4129 867.7072) 
(list 1280.4172 867.7175) 
(list 1280.4216 867.7278) 
(list 1280.4259 867.7381) 
(list 1280.4301 867.7483) 
(list 1280.4339 867.7586) 
(list 1280.4373 867.7689) 
(list 1280.4402 867.7792) 
(list 1280.4424 867.7894) 
(list 1280.4438 867.7997) 
(list 1280.4445 867.81) 
(list 1280.4445 867.81)))
(apply 'command (append '("pline") coords '("c")))
(setq tap4 (ssadd (entlast) tap4))
(command "_mirror" (entlast) "" "1280,900" "1280,901" "No")
(setq tap4 (ssadd (entlast) tap4))
(setq coords (list 
(list 1281.125 867.44) 
(list 1280.4445 867.44) 
(list 1280.4445 867.4503) 
(list 1280.4445 867.4606) 
(list 1280.4445 867.4708) 
(list 1280.4445 867.4811) 
(list 1280.4445 867.4914) 
(list 1280.4445 867.5017) 
(list 1280.4445 867.5119) 
(list 1280.4445 867.5222) 
(list 1280.4445 867.5325) 
(list 1280.4445 867.5428) 
(list 1280.4445 867.5531) 
(list 1280.4445 867.5633) 
(list 1280.4445 867.5736) 
(list 1280.4445 867.5839) 
(list 1280.4445 867.5942) 
(list 1280.4445 867.6044) 
(list 1280.4445 867.6147) 
(list 1280.4445 867.625) 
(list 1280.4445 867.6353) 
(list 1280.4445 867.6456) 
(list 1280.4445 867.6558) 
(list 1280.4445 867.6661) 
(list 1280.4445 867.6764) 
(list 1280.4445 867.6867) 
(list 1280.4445 867.6969) 
(list 1280.4445 867.7072) 
(list 1280.4445 867.7175) 
(list 1280.4445 867.7278) 
(list 1280.4445 867.7381) 
(list 1280.4445 867.7483) 
(list 1280.4445 867.7586) 
(list 1280.4445 867.7689) 
(list 1280.4445 867.7792) 
(list 1280.4445 867.7894) 
(list 1280.4445 867.7997) 
(list 1280.4445 867.81) 
(list 1281.125 867.81)))
(apply 'command (append '("pline") coords '("c")))
(setq tap4 (ssadd (entlast) tap4))
(command "_mirror" (entlast) "" "1280,900" "1280,901" "No")
(setq tap4 (ssadd (entlast) tap4))
(setq coords (list 
(list 1280 867.81) 
(list 1280.135 867.81) 
(list 1280.135 867.8203) 
(list 1280.135 867.8306) 
(list 1280.135 867.8408) 
(list 1280.135 867.8511) 
(list 1280.135 867.8614) 
(list 1280.135 867.8717) 
(list 1280.135 867.8819) 
(list 1280.135 867.8922) 
(list 1280.135 867.9025) 
(list 1280.135 867.9128) 
(list 1280.135 867.9231) 
(list 1280.135 867.9333) 
(list 1280.135 867.9436) 
(list 1280.135 867.9539) 
(list 1280.135 867.9642) 
(list 1280.135 867.9744) 
(list 1280.135 867.9847) 
(list 1280.135 867.995) 
(list 1280.135 868.0053) 
(list 1280.135 868.0156) 
(list 1280.135 868.0258) 
(list 1280.135 868.0361) 
(list 1280.135 868.0464) 
(list 1280.135 868.0567) 
(list 1280.135 868.0669) 
(list 1280.135 868.0772) 
(list 1280.135 868.0875) 
(list 1280.135 868.0978) 
(list 1280.135 868.1081) 
(list 1280.135 868.1183) 
(list 1280.135 868.1286) 
(list 1280.135 868.1389) 
(list 1280.135 868.1492) 
(list 1280.135 868.1594) 
(list 1280.135 868.1697) 
(list 1280.135 868.18) 
(list 1280 868.18)))
(apply 'command (append '("pline") coords '("c")))
(setq tap4 (ssadd (entlast) tap4))
(command "_mirror" (entlast) "" "1280,900" "1280,901" "No")
(setq tap4 (ssadd (entlast) tap4))
(setq coords (list 
(list 1280.4543 867.81) 
(list 1280.4445 867.81) 
(list 1280.4444 867.8203) 
(list 1280.4434 867.8306) 
(list 1280.4416 867.8408) 
(list 1280.439 867.8511) 
(list 1280.4357 867.8614) 
(list 1280.4318 867.8717) 
(list 1280.4274 867.8819) 
(list 1280.4226 867.8922) 
(list 1280.4176 867.9025) 
(list 1280.4125 867.9128) 
(list 1280.4074 867.9231) 
(list 1280.4026 867.9333) 
(list 1280.3982 867.9436) 
(list 1280.3943 867.9539) 
(list 1280.391 867.9642) 
(list 1280.3885 867.9744) 
(list 1280.3869 867.9847) 
(list 1280.3862 867.995) 
(list 1280.3864 868.0053) 
(list 1280.3877 868.0156) 
(list 1280.3898 868.0258) 
(list 1280.3929 868.0361) 
(list 1280.3968 868.0464) 
(list 1280.4014 868.0567) 
(list 1280.4065 868.0669) 
(list 1280.4121 868.0772) 
(list 1280.418 868.0875) 
(list 1280.4239 868.0978) 
(list 1280.4298 868.1081) 
(list 1280.4354 868.1183) 
(list 1280.4405 868.1286) 
(list 1280.445 868.1389) 
(list 1280.4488 868.1492) 
(list 1280.4516 868.1594) 
(list 1280.4535 868.1697) 
(list 1280.4543 868.18) 
(list 1280.4543 868.18)))
(apply 'command (append '("pline") coords '("c")))
(setq tap4 (ssadd (entlast) tap4))
(command "_mirror" (entlast) "" "1280,900" "1280,901" "No")
(setq tap4 (ssadd (entlast) tap4))
(setq coords (list 
(list 1281.125 867.81) 
(list 1280.4543 867.81) 
(list 1280.4543 867.8203) 
(list 1280.4543 867.8306) 
(list 1280.4543 867.8408) 
(list 1280.4543 867.8511) 
(list 1280.4543 867.8614) 
(list 1280.4543 867.8717) 
(list 1280.4543 867.8819) 
(list 1280.4543 867.8922) 
(list 1280.4543 867.9025) 
(list 1280.4543 867.9128) 
(list 1280.4543 867.9231) 
(list 1280.4543 867.9333) 
(list 1280.4543 867.9436) 
(list 1280.4543 867.9539) 
(list 1280.4543 867.9642) 
(list 1280.4543 867.9744) 
(list 1280.4543 867.9847) 
(list 1280.4543 867.995) 
(list 1280.4543 868.0053) 
(list 1280.4543 868.0156) 
(list 1280.4543 868.0258) 
(list 1280.4543 868.0361) 
(list 1280.4543 868.0464) 
(list 1280.4543 868.0567) 
(list 1280.4543 868.0669) 
(list 1280.4543 868.0772) 
(list 1280.4543 868.0875) 
(list 1280.4543 868.0978) 
(list 1280.4543 868.1081) 
(list 1280.4543 868.1183) 
(list 1280.4543 868.1286) 
(list 1280.4543 868.1389) 
(list 1280.4543 868.1492) 
(list 1280.4543 868.1594) 
(list 1280.4543 868.1697) 
(list 1280.4543 868.18) 
(list 1281.125 868.18)))
(apply 'command (append '("pline") coords '("c")))
(setq tap4 (ssadd (entlast) tap4))
(command "_mirror" (entlast) "" "1280,900" "1280,901" "No")
(setq tap4 (ssadd (entlast) tap4))
(setq coords (list 
(list 1280 868.18) 
(list 1280.135 868.18) 
(list 1280.135 868.1903) 
(list 1280.135 868.2006) 
(list 1280.135 868.2108) 
(list 1280.135 868.2211) 
(list 1280.135 868.2314) 
(list 1280.135 868.2417) 
(list 1280.135 868.2519) 
(list 1280.135 868.2622) 
(list 1280.135 868.2725) 
(list 1280.135 868.2828) 
(list 1280.135 868.2931) 
(list 1280.135 868.3033) 
(list 1280.135 868.3136) 
(list 1280.135 868.3239) 
(list 1280.135 868.3342) 
(list 1280.135 868.3444) 
(list 1280.135 868.3547) 
(list 1280.135 868.365) 
(list 1280.135 868.3753) 
(list 1280.135 868.3856) 
(list 1280.135 868.3958) 
(list 1280.135 868.4061) 
(list 1280.135 868.4164) 
(list 1280.135 868.4267) 
(list 1280.135 868.4369) 
(list 1280.135 868.4472) 
(list 1280.135 868.4575) 
(list 1280.135 868.4678) 
(list 1280.135 868.4781) 
(list 1280.135 868.4883) 
(list 1280.135 868.4986) 
(list 1280.135 868.5089) 
(list 1280.135 868.5192) 
(list 1280.135 868.5294) 
(list 1280.135 868.5397) 
(list 1280.135 868.55) 
(list 1280 868.55)))
(apply 'command (append '("pline") coords '("c")))
(setq tap4 (ssadd (entlast) tap4))
(command "_mirror" (entlast) "" "1280,900" "1280,901" "No")
(setq tap4 (ssadd (entlast) tap4))
(setq coords (list 
(list 1280.4642 868.18) 
(list 1280.4543 868.18) 
(list 1280.4541 868.1903) 
(list 1280.4527 868.2006) 
(list 1280.4502 868.2108) 
(list 1280.4467 868.2211) 
(list 1280.4423 868.2314) 
(list 1280.4372 868.2417) 
(list 1280.4313 868.2519) 
(list 1280.425 868.2622) 
(list 1280.4184 868.2725) 
(list 1280.4117 868.2828) 
(list 1280.4051 868.2931) 
(list 1280.3989 868.3033) 
(list 1280.3932 868.3136) 
(list 1280.3881 868.3239) 
(list 1280.384 868.3342) 
(list 1280.3808 868.3444) 
(list 1280.3788 868.3547) 
(list 1280.378 868.365) 
(list 1280.3783 868.3753) 
(list 1280.38 868.3856) 
(list 1280.3828 868.3958) 
(list 1280.3868 868.4061) 
(list 1280.3918 868.4164) 
(list 1280.3977 868.4267) 
(list 1280.4043 868.4369) 
(list 1280.4114 868.4472) 
(list 1280.4188 868.4575) 
(list 1280.4263 868.4678) 
(list 1280.4337 868.4781) 
(list 1280.4407 868.4883) 
(list 1280.4471 868.4986) 
(list 1280.4527 868.5089) 
(list 1280.4574 868.5192) 
(list 1280.4609 868.5294) 
(list 1280.4632 868.5397) 
(list 1280.4642 868.55) 
(list 1280.4642 868.55)))
(apply 'command (append '("pline") coords '("c")))
(setq tap4 (ssadd (entlast) tap4))
(command "_mirror" (entlast) "" "1280,900" "1280,901" "No")
(setq tap4 (ssadd (entlast) tap4))
(setq coords (list 
(list 1281.125 868.18) 
(list 1280.4642 868.18) 
(list 1280.4642 868.1903) 
(list 1280.4642 868.2006) 
(list 1280.4642 868.2108) 
(list 1280.4642 868.2211) 
(list 1280.4642 868.2314) 
(list 1280.4642 868.2417) 
(list 1280.4642 868.2519) 
(list 1280.4642 868.2622) 
(list 1280.4642 868.2725) 
(list 1280.4642 868.2828) 
(list 1280.4642 868.2931) 
(list 1280.4642 868.3033) 
(list 1280.4642 868.3136) 
(list 1280.4642 868.3239) 
(list 1280.4642 868.3342) 
(list 1280.4642 868.3444) 
(list 1280.4642 868.3547) 
(list 1280.4642 868.365) 
(list 1280.4642 868.3753) 
(list 1280.4642 868.3856) 
(list 1280.4642 868.3958) 
(list 1280.4642 868.4061) 
(list 1280.4642 868.4164) 
(list 1280.4642 868.4267) 
(list 1280.4642 868.4369) 
(list 1280.4642 868.4472) 
(list 1280.4642 868.4575) 
(list 1280.4642 868.4678) 
(list 1280.4642 868.4781) 
(list 1280.4642 868.4883) 
(list 1280.4642 868.4986) 
(list 1280.4642 868.5089) 
(list 1280.4642 868.5192) 
(list 1280.4642 868.5294) 
(list 1280.4642 868.5397) 
(list 1280.4642 868.55) 
(list 1281.125 868.55)))
(apply 'command (append '("pline") coords '("c")))
(setq tap4 (ssadd (entlast) tap4))
(command "_mirror" (entlast) "" "1280,900" "1280,901" "No")
(setq tap4 (ssadd (entlast) tap4))
(setq coords (list 
(list 1280 868.55) 
(list 1280.135 868.55) 
(list 1280.135 868.5603) 
(list 1280.135 868.5706) 
(list 1280.135 868.5808) 
(list 1280.135 868.5911) 
(list 1280.135 868.6014) 
(list 1280.135 868.6117) 
(list 1280.135 868.6219) 
(list 1280.135 868.6322) 
(list 1280.135 868.6425) 
(list 1280.135 868.6528) 
(list 1280.135 868.6631) 
(list 1280.135 868.6733) 
(list 1280.135 868.6836) 
(list 1280.135 868.6939) 
(list 1280.135 868.7042) 
(list 1280.135 868.7144) 
(list 1280.135 868.7247) 
(list 1280.135 868.735) 
(list 1280.135 868.7453) 
(list 1280.135 868.7556) 
(list 1280.135 868.7658) 
(list 1280.135 868.7761) 
(list 1280.135 868.7864) 
(list 1280.135 868.7967) 
(list 1280.135 868.8069) 
(list 1280.135 868.8172) 
(list 1280.135 868.8275) 
(list 1280.135 868.8378) 
(list 1280.135 868.8481) 
(list 1280.135 868.8583) 
(list 1280.135 868.8686) 
(list 1280.135 868.8789) 
(list 1280.135 868.8892) 
(list 1280.135 868.8994) 
(list 1280.135 868.9097) 
(list 1280.135 868.92) 
(list 1280 868.92)))
(apply 'command (append '("pline") coords '("c")))
(setq tap4 (ssadd (entlast) tap4))
(command "_mirror" (entlast) "" "1280,900" "1280,901" "No")
(setq tap4 (ssadd (entlast) tap4))
(setq coords (list 
(list 1280.474 868.55) 
(list 1280.4642 868.55) 
(list 1280.4637 868.5603) 
(list 1280.462 868.5706) 
(list 1280.4588 868.5808) 
(list 1280.4545 868.5911) 
(list 1280.4489 868.6014) 
(list 1280.4425 868.6117) 
(list 1280.4352 868.6219) 
(list 1280.4274 868.6322) 
(list 1280.4192 868.6425) 
(list 1280.4109 868.6528) 
(list 1280.4029 868.6631) 
(list 1280.3952 868.6733) 
(list 1280.3882 868.6836) 
(list 1280.382 868.6939) 
(list 1280.377 868.7042) 
(list 1280.3731 868.7144) 
(list 1280.3707 868.7247) 
(list 1280.3697 868.735) 
(list 1280.3702 868.7453) 
(list 1280.3723 868.7556) 
(list 1280.3758 868.7658) 
(list 1280.3807 868.7761) 
(list 1280.3868 868.7864) 
(list 1280.3939 868.7967) 
(list 1280.402 868.8069) 
(list 1280.4106 868.8172) 
(list 1280.4196 868.8275) 
(list 1280.4287 868.8378) 
(list 1280.4376 868.8481) 
(list 1280.446 868.8583) 
(list 1280.4537 868.8686) 
(list 1280.4605 868.8789) 
(list 1280.466 868.8892) 
(list 1280.4702 868.8994) 
(list 1280.4729 868.9097) 
(list 1280.474 868.92) 
(list 1280.474 868.92)))
(apply 'command (append '("pline") coords '("c")))
(setq tap4 (ssadd (entlast) tap4))
(command "_mirror" (entlast) "" "1280,900" "1280,901" "No")
(setq tap4 (ssadd (entlast) tap4))
(setq coords (list 
(list 1281.125 868.55) 
(list 1280.474 868.55) 
(list 1280.474 868.5603) 
(list 1280.474 868.5706) 
(list 1280.474 868.5808) 
(list 1280.474 868.5911) 
(list 1280.474 868.6014) 
(list 1280.474 868.6117) 
(list 1280.474 868.6219) 
(list 1280.474 868.6322) 
(list 1280.474 868.6425) 
(list 1280.474 868.6528) 
(list 1280.474 868.6631) 
(list 1280.474 868.6733) 
(list 1280.474 868.6836) 
(list 1280.474 868.6939) 
(list 1280.474 868.7042) 
(list 1280.474 868.7144) 
(list 1280.474 868.7247) 
(list 1280.474 868.735) 
(list 1280.474 868.7453) 
(list 1280.474 868.7556) 
(list 1280.474 868.7658) 
(list 1280.474 868.7761) 
(list 1280.474 868.7864) 
(list 1280.474 868.7967) 
(list 1280.474 868.8069) 
(list 1280.474 868.8172) 
(list 1280.474 868.8275) 
(list 1280.474 868.8378) 
(list 1280.474 868.8481) 
(list 1280.474 868.8583) 
(list 1280.474 868.8686) 
(list 1280.474 868.8789) 
(list 1280.474 868.8892) 
(list 1280.474 868.8994) 
(list 1280.474 868.9097) 
(list 1280.474 868.92) 
(list 1281.125 868.92)))
(apply 'command (append '("pline") coords '("c")))
(setq tap4 (ssadd (entlast) tap4))
(command "_mirror" (entlast) "" "1280,900" "1280,901" "No")
(setq tap4 (ssadd (entlast) tap4))
(setq coords (list 
(list 1280 868.92) 
(list 1280.135 868.92) 
(list 1280.135 868.9303) 
(list 1280.135 868.9406) 
(list 1280.135 868.9508) 
(list 1280.135 868.9611) 
(list 1280.135 868.9714) 
(list 1280.135 868.9817) 
(list 1280.135 868.9919) 
(list 1280.135 869.0022) 
(list 1280.135 869.0125) 
(list 1280.135 869.0228) 
(list 1280.135 869.0331) 
(list 1280.135 869.0433) 
(list 1280.135 869.0536) 
(list 1280.135 869.0639) 
(list 1280.135 869.0742) 
(list 1280.135 869.0844) 
(list 1280.135 869.0947) 
(list 1280.135 869.105) 
(list 1280.135 869.1153) 
(list 1280.135 869.1256) 
(list 1280.135 869.1358) 
(list 1280.135 869.1461) 
(list 1280.135 869.1564) 
(list 1280.135 869.1667) 
(list 1280.135 869.1769) 
(list 1280.135 869.1872) 
(list 1280.135 869.1975) 
(list 1280.135 869.2078) 
(list 1280.135 869.2181) 
(list 1280.135 869.2283) 
(list 1280.135 869.2386) 
(list 1280.135 869.2489) 
(list 1280.135 869.2592) 
(list 1280.135 869.2694) 
(list 1280.135 869.2797) 
(list 1280.135 869.29) 
(list 1280 869.29)))
(apply 'command (append '("pline") coords '("c")))
(setq tap4 (ssadd (entlast) tap4))
(command "_mirror" (entlast) "" "1280,900" "1280,901" "No")
(setq tap4 (ssadd (entlast) tap4))
(setq coords (list 
(list 1280.4838 868.92) 
(list 1280.474 868.92) 
(list 1280.4734 868.9303) 
(list 1280.4712 868.9406) 
(list 1280.4675 868.9508) 
(list 1280.4622 868.9611) 
(list 1280.4556 868.9714) 
(list 1280.4478 868.9817) 
(list 1280.4391 868.9919) 
(list 1280.4297 869.0022) 
(list 1280.42 869.0125) 
(list 1280.4102 869.0228) 
(list 1280.4006 869.0331) 
(list 1280.3915 869.0433) 
(list 1280.3832 869.0536) 
(list 1280.3759 869.0639) 
(list 1280.3699 869.0742) 
(list 1280.3655 869.0844) 
(list 1280.3626 869.0947) 
(list 1280.3615 869.105) 
(list 1280.3622 869.1153) 
(list 1280.3646 869.1256) 
(list 1280.3688 869.1358) 
(list 1280.3745 869.1461) 
(list 1280.3818 869.1564) 
(list 1280.3902 869.1667) 
(list 1280.3997 869.1769) 
(list 1280.4098 869.1872) 
(list 1280.4204 869.1975) 
(list 1280.4311 869.2078) 
(list 1280.4415 869.2181) 
(list 1280.4513 869.2283) 
(list 1280.4603 869.2386) 
(list 1280.4682 869.2489) 
(list 1280.4746 869.2592) 
(list 1280.4795 869.2694) 
(list 1280.4826 869.2797) 
(list 1280.4838 869.29) 
(list 1280.4838 869.29)))
(apply 'command (append '("pline") coords '("c")))
(setq tap4 (ssadd (entlast) tap4))
(command "_mirror" (entlast) "" "1280,900" "1280,901" "No")
(setq tap4 (ssadd (entlast) tap4))
(setq coords (list 
(list 1281.125 868.92) 
(list 1280.4838 868.92) 
(list 1280.4838 868.9303) 
(list 1280.4838 868.9406) 
(list 1280.4838 868.9508) 
(list 1280.4838 868.9611) 
(list 1280.4838 868.9714) 
(list 1280.4838 868.9817) 
(list 1280.4838 868.9919) 
(list 1280.4838 869.0022) 
(list 1280.4838 869.0125) 
(list 1280.4838 869.0228) 
(list 1280.4838 869.0331) 
(list 1280.4838 869.0433) 
(list 1280.4838 869.0536) 
(list 1280.4838 869.0639) 
(list 1280.4838 869.0742) 
(list 1280.4838 869.0844) 
(list 1280.4838 869.0947) 
(list 1280.4838 869.105) 
(list 1280.4838 869.1153) 
(list 1280.4838 869.1256) 
(list 1280.4838 869.1358) 
(list 1280.4838 869.1461) 
(list 1280.4838 869.1564) 
(list 1280.4838 869.1667) 
(list 1280.4838 869.1769) 
(list 1280.4838 869.1872) 
(list 1280.4838 869.1975) 
(list 1280.4838 869.2078) 
(list 1280.4838 869.2181) 
(list 1280.4838 869.2283) 
(list 1280.4838 869.2386) 
(list 1280.4838 869.2489) 
(list 1280.4838 869.2592) 
(list 1280.4838 869.2694) 
(list 1280.4838 869.2797) 
(list 1280.4838 869.29) 
(list 1281.125 869.29)))
(apply 'command (append '("pline") coords '("c")))
(setq tap4 (ssadd (entlast) tap4))
(command "_mirror" (entlast) "" "1280,900" "1280,901" "No")
(setq tap4 (ssadd (entlast) tap4))
(setq coords (list 
(list 1280 869.29) 
(list 1280.135 869.29) 
(list 1280.135 869.3003) 
(list 1280.135 869.3106) 
(list 1280.135 869.3208) 
(list 1280.135 869.3311) 
(list 1280.135 869.3414) 
(list 1280.135 869.3517) 
(list 1280.135 869.3619) 
(list 1280.135 869.3722) 
(list 1280.135 869.3825) 
(list 1280.135 869.3928) 
(list 1280.135 869.4031) 
(list 1280.135 869.4133) 
(list 1280.135 869.4236) 
(list 1280.135 869.4339) 
(list 1280.135 869.4442) 
(list 1280.135 869.4544) 
(list 1280.135 869.4647) 
(list 1280.135 869.475) 
(list 1280.135 869.4853) 
(list 1280.135 869.4956) 
(list 1280.135 869.5058) 
(list 1280.135 869.5161) 
(list 1280.135 869.5264) 
(list 1280.135 869.5367) 
(list 1280.135 869.5469) 
(list 1280.135 869.5572) 
(list 1280.135 869.5675) 
(list 1280.135 869.5778) 
(list 1280.135 869.5881) 
(list 1280.135 869.5983) 
(list 1280.135 869.6086) 
(list 1280.135 869.6189) 
(list 1280.135 869.6292) 
(list 1280.135 869.6394) 
(list 1280.135 869.6497) 
(list 1280.135 869.66) 
(list 1280 869.66)))
(apply 'command (append '("pline") coords '("c")))
(setq tap4 (ssadd (entlast) tap4))
(command "_mirror" (entlast) "" "1280,900" "1280,901" "No")
(setq tap4 (ssadd (entlast) tap4))
(setq coords (list 
(list 1280.4937 869.29) 
(list 1280.4838 869.29) 
(list 1280.4831 869.3003) 
(list 1280.4805 869.3106) 
(list 1280.4761 869.3208) 
(list 1280.4699 869.3311) 
(list 1280.4622 869.3414) 
(list 1280.4531 869.3517) 
(list 1280.443 869.3619) 
(list 1280.4321 869.3722) 
(list 1280.4208 869.3825) 
(list 1280.4094 869.3928) 
(list 1280.3983 869.4031) 
(list 1280.3877 869.4133) 
(list 1280.3781 869.4236) 
(list 1280.3698 869.4339) 
(list 1280.3629 869.4442) 
(list 1280.3578 869.4544) 
(list 1280.3545 869.4647) 
(list 1280.3532 869.475) 
(list 1280.3541 869.4853) 
(list 1280.3569 869.4956) 
(list 1280.3617 869.5058) 
(list 1280.3684 869.5161) 
(list 1280.3768 869.5264) 
(list 1280.3865 869.5367) 
(list 1280.3974 869.5469) 
(list 1280.4091 869.5572) 
(list 1280.4212 869.5675) 
(list 1280.4334 869.5778) 
(list 1280.4454 869.5881) 
(list 1280.4566 869.5983) 
(list 1280.4669 869.6086) 
(list 1280.4759 869.6189) 
(list 1280.4833 869.6292) 
(list 1280.4888 869.6394) 
(list 1280.4923 869.6497) 
(list 1280.4937 869.66) 
(list 1280.4937 869.66)))
(apply 'command (append '("pline") coords '("c")))
(setq tap4 (ssadd (entlast) tap4))
(command "_mirror" (entlast) "" "1280,900" "1280,901" "No")
(setq tap4 (ssadd (entlast) tap4))
(setq coords (list 
(list 1281.125 869.29) 
(list 1280.4937 869.29) 
(list 1280.4937 869.3003) 
(list 1280.4937 869.3106) 
(list 1280.4937 869.3208) 
(list 1280.4937 869.3311) 
(list 1280.4937 869.3414) 
(list 1280.4937 869.3517) 
(list 1280.4937 869.3619) 
(list 1280.4937 869.3722) 
(list 1280.4937 869.3825) 
(list 1280.4937 869.3928) 
(list 1280.4937 869.4031) 
(list 1280.4937 869.4133) 
(list 1280.4937 869.4236) 
(list 1280.4937 869.4339) 
(list 1280.4937 869.4442) 
(list 1280.4937 869.4544) 
(list 1280.4937 869.4647) 
(list 1280.4937 869.475) 
(list 1280.4937 869.4853) 
(list 1280.4937 869.4956) 
(list 1280.4937 869.5058) 
(list 1280.4937 869.5161) 
(list 1280.4937 869.5264) 
(list 1280.4937 869.5367) 
(list 1280.4937 869.5469) 
(list 1280.4937 869.5572) 
(list 1280.4937 869.5675) 
(list 1280.4937 869.5778) 
(list 1280.4937 869.5881) 
(list 1280.4937 869.5983) 
(list 1280.4937 869.6086) 
(list 1280.4937 869.6189) 
(list 1280.4937 869.6292) 
(list 1280.4937 869.6394) 
(list 1280.4937 869.6497) 
(list 1280.4937 869.66) 
(list 1281.125 869.66)))
(apply 'command (append '("pline") coords '("c")))
(setq tap4 (ssadd (entlast) tap4))
(command "_mirror" (entlast) "" "1280,900" "1280,901" "No")
(setq tap4 (ssadd (entlast) tap4))
(setq coords (list 
(list 1280 869.66) 
(list 1280.135 869.66) 
(list 1280.135 869.6703) 
(list 1280.135 869.6806) 
(list 1280.135 869.6908) 
(list 1280.135 869.7011) 
(list 1280.135 869.7114) 
(list 1280.135 869.7217) 
(list 1280.135 869.7319) 
(list 1280.135 869.7422) 
(list 1280.135 869.7525) 
(list 1280.135 869.7628) 
(list 1280.135 869.7731) 
(list 1280.135 869.7833) 
(list 1280.135 869.7936) 
(list 1280.135 869.8039) 
(list 1280.135 869.8142) 
(list 1280.135 869.8244) 
(list 1280.135 869.8347) 
(list 1280.135 869.845) 
(list 1280.135 869.8553) 
(list 1280.135 869.8656) 
(list 1280.135 869.8758) 
(list 1280.135 869.8861) 
(list 1280.135 869.8964) 
(list 1280.135 869.9067) 
(list 1280.135 869.9169) 
(list 1280.135 869.9272) 
(list 1280.135 869.9375) 
(list 1280.135 869.9478) 
(list 1280.135 869.9581) 
(list 1280.135 869.9683) 
(list 1280.135 869.9786) 
(list 1280.135 869.9889) 
(list 1280.135 869.9992) 
(list 1280.135 870.0094) 
(list 1280.135 870.0197) 
(list 1280.135 870.03) 
(list 1280 870.03)))
(apply 'command (append '("pline") coords '("c")))
(setq tap4 (ssadd (entlast) tap4))
(command "_mirror" (entlast) "" "1280,900" "1280,901" "No")
(setq tap4 (ssadd (entlast) tap4))
(setq coords (list 
(list 1280.5035 869.66) 
(list 1280.4937 869.66) 
(list 1280.4928 869.6703) 
(list 1280.4898 869.6806) 
(list 1280.4847 869.6908) 
(list 1280.4776 869.7011) 
(list 1280.4688 869.7114) 
(list 1280.4584 869.7217) 
(list 1280.4469 869.7319) 
(list 1280.4345 869.7422) 
(list 1280.4216 869.7525) 
(list 1280.4086 869.7628) 
(list 1280.396 869.7731) 
(list 1280.384 869.7833) 
(list 1280.3731 869.7936) 
(list 1280.3637 869.8039) 
(list 1280.3559 869.8142) 
(list 1280.3501 869.8244) 
(list 1280.3464 869.8347) 
(list 1280.345 869.845) 
(list 1280.346 869.8553) 
(list 1280.3492 869.8656) 
(list 1280.3547 869.8758) 
(list 1280.3623 869.8861) 
(list 1280.3717 869.8964) 
(list 1280.3828 869.9067) 
(list 1280.3951 869.9169) 
(list 1280.4083 869.9272) 
(list 1280.422 869.9375) 
(list 1280.4358 869.9478) 
(list 1280.4492 869.9581) 
(list 1280.462 869.9683) 
(list 1280.4735 869.9786) 
(list 1280.4836 869.9889) 
(list 1280.4919 869.9992) 
(list 1280.4981 870.0094) 
(list 1280.502 870.0197) 
(list 1280.5035 870.03) 
(list 1280.5035 870.03)))
(apply 'command (append '("pline") coords '("c")))
(setq tap4 (ssadd (entlast) tap4))
(command "_mirror" (entlast) "" "1280,900" "1280,901" "No")
(setq tap4 (ssadd (entlast) tap4))
(setq coords (list 
(list 1281.125 869.66) 
(list 1280.5035 869.66) 
(list 1280.5035 869.6703) 
(list 1280.5035 869.6806) 
(list 1280.5035 869.6908) 
(list 1280.5035 869.7011) 
(list 1280.5035 869.7114) 
(list 1280.5035 869.7217) 
(list 1280.5035 869.7319) 
(list 1280.5035 869.7422) 
(list 1280.5035 869.7525) 
(list 1280.5035 869.7628) 
(list 1280.5035 869.7731) 
(list 1280.5035 869.7833) 
(list 1280.5035 869.7936) 
(list 1280.5035 869.8039) 
(list 1280.5035 869.8142) 
(list 1280.5035 869.8244) 
(list 1280.5035 869.8347) 
(list 1280.5035 869.845) 
(list 1280.5035 869.8553) 
(list 1280.5035 869.8656) 
(list 1280.5035 869.8758) 
(list 1280.5035 869.8861) 
(list 1280.5035 869.8964) 
(list 1280.5035 869.9067) 
(list 1280.5035 869.9169) 
(list 1280.5035 869.9272) 
(list 1280.5035 869.9375) 
(list 1280.5035 869.9478) 
(list 1280.5035 869.9581) 
(list 1280.5035 869.9683) 
(list 1280.5035 869.9786) 
(list 1280.5035 869.9889) 
(list 1280.5035 869.9992) 
(list 1280.5035 870.0094) 
(list 1280.5035 870.0197) 
(list 1280.5035 870.03) 
(list 1281.125 870.03)))
(apply 'command (append '("pline") coords '("c")))
(setq tap4 (ssadd (entlast) tap4))
(command "_mirror" (entlast) "" "1280,900" "1280,901" "No")
(setq tap4 (ssadd (entlast) tap4))
(setq coords (list 
(list 1280 870.03) 
(list 1280.135 870.03) 
(list 1280.135 870.0403) 
(list 1280.135 870.0506) 
(list 1280.135 870.0608) 
(list 1280.135 870.0711) 
(list 1280.135 870.0814) 
(list 1280.135 870.0917) 
(list 1280.135 870.1019) 
(list 1280.135 870.1122) 
(list 1280.135 870.1225) 
(list 1280.135 870.1328) 
(list 1280.135 870.1431) 
(list 1280.135 870.1533) 
(list 1280.135 870.1636) 
(list 1280.135 870.1739) 
(list 1280.135 870.1842) 
(list 1280.135 870.1944) 
(list 1280.135 870.2047) 
(list 1280.135 870.215) 
(list 1280.135 870.2253) 
(list 1280.135 870.2356) 
(list 1280.135 870.2458) 
(list 1280.135 870.2561) 
(list 1280.135 870.2664) 
(list 1280.135 870.2767) 
(list 1280.135 870.2869) 
(list 1280.135 870.2972) 
(list 1280.135 870.3075) 
(list 1280.135 870.3178) 
(list 1280.135 870.3281) 
(list 1280.135 870.3383) 
(list 1280.135 870.3486) 
(list 1280.135 870.3589) 
(list 1280.135 870.3692) 
(list 1280.135 870.3794) 
(list 1280.135 870.3897) 
(list 1280.135 870.4) 
(list 1280 870.4)))
(apply 'command (append '("pline") coords '("c")))
(setq tap4 (ssadd (entlast) tap4))
(command "_mirror" (entlast) "" "1280,900" "1280,901" "No")
(setq tap4 (ssadd (entlast) tap4))
(setq coords (list 
(list 1280.5133 870.03) 
(list 1280.5035 870.03) 
(list 1280.5025 870.0403) 
(list 1280.4991 870.0506) 
(list 1280.4933 870.0608) 
(list 1280.4853 870.0711) 
(list 1280.4754 870.0814) 
(list 1280.4637 870.0917) 
(list 1280.4508 870.1019) 
(list 1280.4368 870.1122) 
(list 1280.4224 870.1225) 
(list 1280.4079 870.1328) 
(list 1280.3937 870.1431) 
(list 1280.3803 870.1533) 
(list 1280.3681 870.1636) 
(list 1280.3575 870.1739) 
(list 1280.3489 870.1842) 
(list 1280.3424 870.1944) 
(list 1280.3383 870.2047) 
(list 1280.3368 870.215) 
(list 1280.3379 870.2253) 
(list 1280.3415 870.2356) 
(list 1280.3477 870.2458) 
(list 1280.3562 870.2561) 
(list 1280.3667 870.2664) 
(list 1280.3791 870.2767) 
(list 1280.3928 870.2869) 
(list 1280.4075 870.2972) 
(list 1280.4228 870.3075) 
(list 1280.4382 870.3178) 
(list 1280.4531 870.3281) 
(list 1280.4673 870.3383) 
(list 1280.4801 870.3486) 
(list 1280.4913 870.3589) 
(list 1280.5005 870.3692) 
(list 1280.5074 870.3794) 
(list 1280.5117 870.3897) 
(list 1280.5133 870.4) 
(list 1280.5133 870.4)))
(apply 'command (append '("pline") coords '("c")))
(setq tap4 (ssadd (entlast) tap4))
(command "_mirror" (entlast) "" "1280,900" "1280,901" "No")
(setq tap4 (ssadd (entlast) tap4))
(setq coords (list 
(list 1281.125 870.03) 
(list 1280.5133 870.03) 
(list 1280.5133 870.0403) 
(list 1280.5133 870.0506) 
(list 1280.5133 870.0608) 
(list 1280.5133 870.0711) 
(list 1280.5133 870.0814) 
(list 1280.5133 870.0917) 
(list 1280.5133 870.1019) 
(list 1280.5133 870.1122) 
(list 1280.5133 870.1225) 
(list 1280.5133 870.1328) 
(list 1280.5133 870.1431) 
(list 1280.5133 870.1533) 
(list 1280.5133 870.1636) 
(list 1280.5133 870.1739) 
(list 1280.5133 870.1842) 
(list 1280.5133 870.1944) 
(list 1280.5133 870.2047) 
(list 1280.5133 870.215) 
(list 1280.5133 870.2253) 
(list 1280.5133 870.2356) 
(list 1280.5133 870.2458) 
(list 1280.5133 870.2561) 
(list 1280.5133 870.2664) 
(list 1280.5133 870.2767) 
(list 1280.5133 870.2869) 
(list 1280.5133 870.2972) 
(list 1280.5133 870.3075) 
(list 1280.5133 870.3178) 
(list 1280.5133 870.3281) 
(list 1280.5133 870.3383) 
(list 1280.5133 870.3486) 
(list 1280.5133 870.3589) 
(list 1280.5133 870.3692) 
(list 1280.5133 870.3794) 
(list 1280.5133 870.3897) 
(list 1280.5133 870.4) 
(list 1281.125 870.4)))
(apply 'command (append '("pline") coords '("c")))
(setq tap4 (ssadd (entlast) tap4))
(command "_mirror" (entlast) "" "1280,900" "1280,901" "No")
(setq tap4 (ssadd (entlast) tap4))
(setq coords (list 
(list 1280 870.4) 
(list 1280.135 870.4) 
(list 1280.135 870.4103) 
(list 1280.135 870.4206) 
(list 1280.135 870.4308) 
(list 1280.135 870.4411) 
(list 1280.135 870.4514) 
(list 1280.135 870.4617) 
(list 1280.135 870.4719) 
(list 1280.135 870.4822) 
(list 1280.135 870.4925) 
(list 1280.135 870.5028) 
(list 1280.135 870.5131) 
(list 1280.135 870.5233) 
(list 1280.135 870.5336) 
(list 1280.135 870.5439) 
(list 1280.135 870.5542) 
(list 1280.135 870.5644) 
(list 1280.135 870.5747) 
(list 1280.135 870.585) 
(list 1280.135 870.5953) 
(list 1280.135 870.6056) 
(list 1280.135 870.6158) 
(list 1280.135 870.6261) 
(list 1280.135 870.6364) 
(list 1280.135 870.6467) 
(list 1280.135 870.6569) 
(list 1280.135 870.6672) 
(list 1280.135 870.6775) 
(list 1280.135 870.6878) 
(list 1280.135 870.6981) 
(list 1280.135 870.7083) 
(list 1280.135 870.7186) 
(list 1280.135 870.7289) 
(list 1280.135 870.7392) 
(list 1280.135 870.7494) 
(list 1280.135 870.7597) 
(list 1280.135 870.77) 
(list 1280 870.77)))
(apply 'command (append '("pline") coords '("c")))
(setq tap4 (ssadd (entlast) tap4))
(command "_mirror" (entlast) "" "1280,900" "1280,901" "No")
(setq tap4 (ssadd (entlast) tap4))
(setq coords (list 
(list 1280.5232 870.4) 
(list 1280.5133 870.4) 
(list 1280.5122 870.4103) 
(list 1280.5084 870.4206) 
(list 1280.5019 870.4308) 
(list 1280.4931 870.4411) 
(list 1280.482 870.4514) 
(list 1280.4691 870.4617) 
(list 1280.4547 870.4719) 
(list 1280.4392 870.4822) 
(list 1280.4232 870.4925) 
(list 1280.4071 870.5028) 
(list 1280.3914 870.5131) 
(list 1280.3766 870.5233) 
(list 1280.3631 870.5336) 
(list 1280.3514 870.5439) 
(list 1280.3418 870.5542) 
(list 1280.3347 870.5644) 
(list 1280.3302 870.5747) 
(list 1280.3285 870.585) 
(list 1280.3298 870.5953) 
(list 1280.3338 870.6056) 
(list 1280.3407 870.6158) 
(list 1280.3501 870.6261) 
(list 1280.3617 870.6364) 
(list 1280.3754 870.6467) 
(list 1280.3905 870.6569) 
(list 1280.4068 870.6672) 
(list 1280.4236 870.6775) 
(list 1280.4405 870.6878) 
(list 1280.457 870.6981) 
(list 1280.4726 870.7083) 
(list 1280.4868 870.7186) 
(list 1280.4991 870.7289) 
(list 1280.5091 870.7392) 
(list 1280.5167 870.7494) 
(list 1280.5214 870.7597) 
(list 1280.5232 870.77) 
(list 1280.5232 870.77)))
(apply 'command (append '("pline") coords '("c")))
(setq tap4 (ssadd (entlast) tap4))
(command "_mirror" (entlast) "" "1280,900" "1280,901" "No")
(setq tap4 (ssadd (entlast) tap4))
(setq coords (list 
(list 1281.125 870.4) 
(list 1280.5232 870.4) 
(list 1280.5232 870.4103) 
(list 1280.5232 870.4206) 
(list 1280.5232 870.4308) 
(list 1280.5232 870.4411) 
(list 1280.5232 870.4514) 
(list 1280.5232 870.4617) 
(list 1280.5232 870.4719) 
(list 1280.5232 870.4822) 
(list 1280.5232 870.4925) 
(list 1280.5232 870.5028) 
(list 1280.5232 870.5131) 
(list 1280.5232 870.5233) 
(list 1280.5232 870.5336) 
(list 1280.5232 870.5439) 
(list 1280.5232 870.5542) 
(list 1280.5232 870.5644) 
(list 1280.5232 870.5747) 
(list 1280.5232 870.585) 
(list 1280.5232 870.5953) 
(list 1280.5232 870.6056) 
(list 1280.5232 870.6158) 
(list 1280.5232 870.6261) 
(list 1280.5232 870.6364) 
(list 1280.5232 870.6467) 
(list 1280.5232 870.6569) 
(list 1280.5232 870.6672) 
(list 1280.5232 870.6775) 
(list 1280.5232 870.6878) 
(list 1280.5232 870.6981) 
(list 1280.5232 870.7083) 
(list 1280.5232 870.7186) 
(list 1280.5232 870.7289) 
(list 1280.5232 870.7392) 
(list 1280.5232 870.7494) 
(list 1280.5232 870.7597) 
(list 1280.5232 870.77) 
(list 1281.125 870.77)))
(apply 'command (append '("pline") coords '("c")))
(setq tap4 (ssadd (entlast) tap4))
(command "_mirror" (entlast) "" "1280,900" "1280,901" "No")
(setq tap4 (ssadd (entlast) tap4))
(setq coords (list 
(list 1280 870.77) 
(list 1280.135 870.77) 
(list 1280.135 870.7803) 
(list 1280.135 870.7906) 
(list 1280.135 870.8008) 
(list 1280.135 870.8111) 
(list 1280.135 870.8214) 
(list 1280.135 870.8317) 
(list 1280.135 870.8419) 
(list 1280.135 870.8522) 
(list 1280.135 870.8625) 
(list 1280.135 870.8728) 
(list 1280.135 870.8831) 
(list 1280.135 870.8933) 
(list 1280.135 870.9036) 
(list 1280.135 870.9139) 
(list 1280.135 870.9242) 
(list 1280.135 870.9344) 
(list 1280.135 870.9447) 
(list 1280.135 870.955) 
(list 1280.135 870.9653) 
(list 1280.135 870.9756) 
(list 1280.135 870.9858) 
(list 1280.135 870.9961) 
(list 1280.135 871.0064) 
(list 1280.135 871.0167) 
(list 1280.135 871.0269) 
(list 1280.135 871.0372) 
(list 1280.135 871.0475) 
(list 1280.135 871.0578) 
(list 1280.135 871.0681) 
(list 1280.135 871.0783) 
(list 1280.135 871.0886) 
(list 1280.135 871.0989) 
(list 1280.135 871.1092) 
(list 1280.135 871.1194) 
(list 1280.135 871.1297) 
(list 1280.135 871.14) 
(list 1280 871.14)))
(apply 'command (append '("pline") coords '("c")))
(setq tap4 (ssadd (entlast) tap4))
(command "_mirror" (entlast) "" "1280,900" "1280,901" "No")
(setq tap4 (ssadd (entlast) tap4))
(setq coords (list 
(list 1280.533 870.77) 
(list 1280.5232 870.77) 
(list 1280.5219 870.7803) 
(list 1280.5177 870.7906) 
(list 1280.5106 870.8008) 
(list 1280.5008 870.8111) 
(list 1280.4886 870.8214) 
(list 1280.4744 870.8317) 
(list 1280.4585 870.8419) 
(list 1280.4416 870.8522) 
(list 1280.424 870.8625) 
(list 1280.4063 870.8728) 
(list 1280.3891 870.8831) 
(list 1280.3729 870.8933) 
(list 1280.3581 870.9036) 
(list 1280.3453 870.9139) 
(list 1280.3348 870.9242) 
(list 1280.327 870.9344) 
(list 1280.3221 870.9447) 
(list 1280.3203 870.955) 
(list 1280.3217 870.9653) 
(list 1280.3262 870.9756) 
(list 1280.3336 870.9858) 
(list 1280.3439 870.9961) 
(list 1280.3567 871.0064) 
(list 1280.3716 871.0167) 
(list 1280.3882 871.0269) 
(list 1280.406 871.0372) 
(list 1280.4244 871.0475) 
(list 1280.4429 871.0578) 
(list 1280.4609 871.0681) 
(list 1280.4779 871.0783) 
(list 1280.4934 871.0886) 
(list 1280.5068 871.0989) 
(list 1280.5178 871.1092) 
(list 1280.5259 871.1194) 
(list 1280.5311 871.1297) 
(list 1280.533 871.14) 
(list 1280.533 871.14)))
(apply 'command (append '("pline") coords '("c")))
(setq tap4 (ssadd (entlast) tap4))
(command "_mirror" (entlast) "" "1280,900" "1280,901" "No")
(setq tap4 (ssadd (entlast) tap4))
(setq coords (list 
(list 1281.125 870.77) 
(list 1280.533 870.77) 
(list 1280.533 870.7803) 
(list 1280.533 870.7906) 
(list 1280.533 870.8008) 
(list 1280.533 870.8111) 
(list 1280.533 870.8214) 
(list 1280.533 870.8317) 
(list 1280.533 870.8419) 
(list 1280.533 870.8522) 
(list 1280.533 870.8625) 
(list 1280.533 870.8728) 
(list 1280.533 870.8831) 
(list 1280.533 870.8933) 
(list 1280.533 870.9036) 
(list 1280.533 870.9139) 
(list 1280.533 870.9242) 
(list 1280.533 870.9344) 
(list 1280.533 870.9447) 
(list 1280.533 870.955) 
(list 1280.533 870.9653) 
(list 1280.533 870.9756) 
(list 1280.533 870.9858) 
(list 1280.533 870.9961) 
(list 1280.533 871.0064) 
(list 1280.533 871.0167) 
(list 1280.533 871.0269) 
(list 1280.533 871.0372) 
(list 1280.533 871.0475) 
(list 1280.533 871.0578) 
(list 1280.533 871.0681) 
(list 1280.533 871.0783) 
(list 1280.533 871.0886) 
(list 1280.533 871.0989) 
(list 1280.533 871.1092) 
(list 1280.533 871.1194) 
(list 1280.533 871.1297) 
(list 1280.533 871.14) 
(list 1281.125 871.14)))
(apply 'command (append '("pline") coords '("c")))
(setq tap4 (ssadd (entlast) tap4))
(command "_mirror" (entlast) "" "1280,900" "1280,901" "No")
(setq tap4 (ssadd (entlast) tap4))
(setq coords (list 
(list 1280 871.14) 
(list 1280.135 871.14) 
(list 1280.135 871.1503) 
(list 1280.135 871.1606) 
(list 1280.135 871.1708) 
(list 1280.135 871.1811) 
(list 1280.135 871.1914) 
(list 1280.135 871.2017) 
(list 1280.135 871.2119) 
(list 1280.135 871.2222) 
(list 1280.135 871.2325) 
(list 1280.135 871.2428) 
(list 1280.135 871.2531) 
(list 1280.135 871.2633) 
(list 1280.135 871.2736) 
(list 1280.135 871.2839) 
(list 1280.135 871.2942) 
(list 1280.135 871.3044) 
(list 1280.135 871.3147) 
(list 1280.135 871.325) 
(list 1280.135 871.3353) 
(list 1280.135 871.3456) 
(list 1280.135 871.3558) 
(list 1280.135 871.3661) 
(list 1280.135 871.3764) 
(list 1280.135 871.3867) 
(list 1280.135 871.3969) 
(list 1280.135 871.4072) 
(list 1280.135 871.4175) 
(list 1280.135 871.4278) 
(list 1280.135 871.4381) 
(list 1280.135 871.4483) 
(list 1280.135 871.4586) 
(list 1280.135 871.4689) 
(list 1280.135 871.4792) 
(list 1280.135 871.4894) 
(list 1280.135 871.4997) 
(list 1280.135 871.51) 
(list 1280 871.51)))
(apply 'command (append '("pline") coords '("c")))
(setq tap4 (ssadd (entlast) tap4))
(command "_mirror" (entlast) "" "1280,900" "1280,901" "No")
(setq tap4 (ssadd (entlast) tap4))
(setq coords (list 
(list 1280.5428 871.14) 
(list 1280.533 871.14) 
(list 1280.5316 871.1503) 
(list 1280.527 871.1606) 
(list 1280.5192 871.1708) 
(list 1280.5085 871.1811) 
(list 1280.4952 871.1914) 
(list 1280.4797 871.2017) 
(list 1280.4624 871.2119) 
(list 1280.444 871.2222) 
(list 1280.4248 871.2325) 
(list 1280.4056 871.2428) 
(list 1280.3868 871.2531) 
(list 1280.3692 871.2633) 
(list 1280.3531 871.2736) 
(list 1280.3392 871.2839) 
(list 1280.3278 871.2942) 
(list 1280.3193 871.3044) 
(list 1280.314 871.3147) 
(list 1280.3121 871.325) 
(list 1280.3136 871.3353) 
(list 1280.3185 871.3456) 
(list 1280.3266 871.3558) 
(list 1280.3378 871.3661) 
(list 1280.3517 871.3764) 
(list 1280.3679 871.3867) 
(list 1280.3859 871.3969) 
(list 1280.4052 871.4072) 
(list 1280.4252 871.4175) 
(list 1280.4453 871.4278) 
(list 1280.4648 871.4381) 
(list 1280.4832 871.4483) 
(list 1280.5 871.4586) 
(list 1280.5145 871.4689) 
(list 1280.5264 871.4792) 
(list 1280.5352 871.4894) 
(list 1280.5408 871.4997) 
(list 1280.5428 871.51) 
(list 1280.5428 871.51)))
(apply 'command (append '("pline") coords '("c")))
(setq tap4 (ssadd (entlast) tap4))
(command "_mirror" (entlast) "" "1280,900" "1280,901" "No")
(setq tap4 (ssadd (entlast) tap4))
(setq coords (list 
(list 1281.125 871.14) 
(list 1280.5428 871.14) 
(list 1280.5428 871.1503) 
(list 1280.5428 871.1606) 
(list 1280.5428 871.1708) 
(list 1280.5428 871.1811) 
(list 1280.5428 871.1914) 
(list 1280.5428 871.2017) 
(list 1280.5428 871.2119) 
(list 1280.5428 871.2222) 
(list 1280.5428 871.2325) 
(list 1280.5428 871.2428) 
(list 1280.5428 871.2531) 
(list 1280.5428 871.2633) 
(list 1280.5428 871.2736) 
(list 1280.5428 871.2839) 
(list 1280.5428 871.2942) 
(list 1280.5428 871.3044) 
(list 1280.5428 871.3147) 
(list 1280.5428 871.325) 
(list 1280.5428 871.3353) 
(list 1280.5428 871.3456) 
(list 1280.5428 871.3558) 
(list 1280.5428 871.3661) 
(list 1280.5428 871.3764) 
(list 1280.5428 871.3867) 
(list 1280.5428 871.3969) 
(list 1280.5428 871.4072) 
(list 1280.5428 871.4175) 
(list 1280.5428 871.4278) 
(list 1280.5428 871.4381) 
(list 1280.5428 871.4483) 
(list 1280.5428 871.4586) 
(list 1280.5428 871.4689) 
(list 1280.5428 871.4792) 
(list 1280.5428 871.4894) 
(list 1280.5428 871.4997) 
(list 1280.5428 871.51) 
(list 1281.125 871.51)))
(apply 'command (append '("pline") coords '("c")))
(setq tap4 (ssadd (entlast) tap4))
(command "_mirror" (entlast) "" "1280,900" "1280,901" "No")
(setq tap4 (ssadd (entlast) tap4))
(setq coords (list 
(list 1280 871.51) 
(list 1280.135 871.51) 
(list 1280.135 871.5203) 
(list 1280.135 871.5306) 
(list 1280.135 871.5408) 
(list 1280.135 871.5511) 
(list 1280.135 871.5614) 
(list 1280.135 871.5717) 
(list 1280.135 871.5819) 
(list 1280.135 871.5922) 
(list 1280.135 871.6025) 
(list 1280.135 871.6128) 
(list 1280.135 871.6231) 
(list 1280.135 871.6333) 
(list 1280.135 871.6436) 
(list 1280.135 871.6539) 
(list 1280.135 871.6642) 
(list 1280.135 871.6744) 
(list 1280.135 871.6847) 
(list 1280.135 871.695) 
(list 1280.135 871.7053) 
(list 1280.135 871.7156) 
(list 1280.135 871.7258) 
(list 1280.135 871.7361) 
(list 1280.135 871.7464) 
(list 1280.135 871.7567) 
(list 1280.135 871.7669) 
(list 1280.135 871.7772) 
(list 1280.135 871.7875) 
(list 1280.135 871.7978) 
(list 1280.135 871.8081) 
(list 1280.135 871.8183) 
(list 1280.135 871.8286) 
(list 1280.135 871.8389) 
(list 1280.135 871.8492) 
(list 1280.135 871.8594) 
(list 1280.135 871.8697) 
(list 1280.135 871.88) 
(list 1280 871.88)))
(apply 'command (append '("pline") coords '("c")))
(setq tap4 (ssadd (entlast) tap4))
(command "_mirror" (entlast) "" "1280,900" "1280,901" "No")
(setq tap4 (ssadd (entlast) tap4))
(setq coords (list 
(list 1280.5527 871.51) 
(list 1280.5428 871.51) 
(list 1280.5413 871.5203) 
(list 1280.5363 871.5306) 
(list 1280.5278 871.5408) 
(list 1280.5162 871.5511) 
(list 1280.5018 871.5614) 
(list 1280.485 871.5717) 
(list 1280.4663 871.5819) 
(list 1280.4463 871.5922) 
(list 1280.4256 871.6025) 
(list 1280.4048 871.6128) 
(list 1280.3845 871.6231) 
(list 1280.3654 871.6333) 
(list 1280.3481 871.6436) 
(list 1280.3331 871.6539) 
(list 1280.3208 871.6642) 
(list 1280.3116 871.6744) 
(list 1280.3059 871.6847) 
(list 1280.3039 871.695) 
(list 1280.3055 871.7053) 
(list 1280.3108 871.7156) 
(list 1280.3196 871.7258) 
(list 1280.3317 871.7361) 
(list 1280.3467 871.7464) 
(list 1280.3642 871.7567) 
(list 1280.3836 871.7669) 
(list 1280.4045 871.7772) 
(list 1280.426 871.7875) 
(list 1280.4476 871.7978) 
(list 1280.4687 871.8081) 
(list 1280.4885 871.8183) 
(list 1280.5066 871.8286) 
(list 1280.5222 871.8389) 
(list 1280.535 871.8492) 
(list 1280.5445 871.8594) 
(list 1280.5505 871.8697) 
(list 1280.5527 871.88) 
(list 1280.5527 871.88)))
(apply 'command (append '("pline") coords '("c")))
(setq tap4 (ssadd (entlast) tap4))
(command "_mirror" (entlast) "" "1280,900" "1280,901" "No")
(setq tap4 (ssadd (entlast) tap4))
(setq coords (list 
(list 1281.125 871.51) 
(list 1280.5527 871.51) 
(list 1280.5527 871.5203) 
(list 1280.5527 871.5306) 
(list 1280.5527 871.5408) 
(list 1280.5527 871.5511) 
(list 1280.5527 871.5614) 
(list 1280.5527 871.5717) 
(list 1280.5527 871.5819) 
(list 1280.5527 871.5922) 
(list 1280.5527 871.6025) 
(list 1280.5527 871.6128) 
(list 1280.5527 871.6231) 
(list 1280.5527 871.6333) 
(list 1280.5527 871.6436) 
(list 1280.5527 871.6539) 
(list 1280.5527 871.6642) 
(list 1280.5527 871.6744) 
(list 1280.5527 871.6847) 
(list 1280.5527 871.695) 
(list 1280.5527 871.7053) 
(list 1280.5527 871.7156) 
(list 1280.5527 871.7258) 
(list 1280.5527 871.7361) 
(list 1280.5527 871.7464) 
(list 1280.5527 871.7567) 
(list 1280.5527 871.7669) 
(list 1280.5527 871.7772) 
(list 1280.5527 871.7875) 
(list 1280.5527 871.7978) 
(list 1280.5527 871.8081) 
(list 1280.5527 871.8183) 
(list 1280.5527 871.8286) 
(list 1280.5527 871.8389) 
(list 1280.5527 871.8492) 
(list 1280.5527 871.8594) 
(list 1280.5527 871.8697) 
(list 1280.5527 871.88) 
(list 1281.125 871.88)))
(apply 'command (append '("pline") coords '("c")))
(setq tap4 (ssadd (entlast) tap4))
(command "_mirror" (entlast) "" "1280,900" "1280,901" "No")
(setq tap4 (ssadd (entlast) tap4))
(setq coords (list 
(list 1280 871.88) 
(list 1280.135 871.88) 
(list 1280.135 871.8903) 
(list 1280.135 871.9006) 
(list 1280.135 871.9108) 
(list 1280.135 871.9211) 
(list 1280.135 871.9314) 
(list 1280.135 871.9417) 
(list 1280.135 871.9519) 
(list 1280.135 871.9622) 
(list 1280.135 871.9725) 
(list 1280.135 871.9828) 
(list 1280.135 871.9931) 
(list 1280.135 872.0033) 
(list 1280.135 872.0136) 
(list 1280.135 872.0239) 
(list 1280.135 872.0342) 
(list 1280.135 872.0444) 
(list 1280.135 872.0547) 
(list 1280.135 872.065) 
(list 1280.135 872.0753) 
(list 1280.135 872.0856) 
(list 1280.135 872.0958) 
(list 1280.135 872.1061) 
(list 1280.135 872.1164) 
(list 1280.135 872.1267) 
(list 1280.135 872.1369) 
(list 1280.135 872.1472) 
(list 1280.135 872.1575) 
(list 1280.135 872.1678) 
(list 1280.135 872.1781) 
(list 1280.135 872.1883) 
(list 1280.135 872.1986) 
(list 1280.135 872.2089) 
(list 1280.135 872.2192) 
(list 1280.135 872.2294) 
(list 1280.135 872.2397) 
(list 1280.135 872.25) 
(list 1280 872.25)))
(apply 'command (append '("pline") coords '("c")))
(setq tap4 (ssadd (entlast) tap4))
(command "_mirror" (entlast) "" "1280,900" "1280,901" "No")
(setq tap4 (ssadd (entlast) tap4))
(setq coords (list 
(list 1280.5625 871.88) 
(list 1280.5527 871.88) 
(list 1280.551 871.8903) 
(list 1280.5456 871.9006) 
(list 1280.5364 871.9108) 
(list 1280.5239 871.9211) 
(list 1280.5084 871.9314) 
(list 1280.4903 871.9417) 
(list 1280.4702 871.9519) 
(list 1280.4487 871.9622) 
(list 1280.4264 871.9725) 
(list 1280.404 871.9828) 
(list 1280.3822 871.9931) 
(list 1280.3617 872.0033) 
(list 1280.3431 872.0136) 
(list 1280.3269 872.0239) 
(list 1280.3138 872.0342) 
(list 1280.3039 872.0444) 
(list 1280.2978 872.0547) 
(list 1280.2956 872.065) 
(list 1280.2974 872.0753) 
(list 1280.3031 872.0856) 
(list 1280.3126 872.0958) 
(list 1280.3256 872.1061) 
(list 1280.3417 872.1164) 
(list 1280.3605 872.1267) 
(list 1280.3814 872.1369) 
(list 1280.4037 872.1472) 
(list 1280.4268 872.1575) 
(list 1280.45 872.1678) 
(list 1280.4726 872.1781) 
(list 1280.4939 872.1883) 
(list 1280.5132 872.1986) 
(list 1280.5299 872.2089) 
(list 1280.5436 872.2192) 
(list 1280.5538 872.2294) 
(list 1280.5602 872.2397) 
(list 1280.5625 872.25) 
(list 1280.5625 872.25)))
(apply 'command (append '("pline") coords '("c")))
(setq tap4 (ssadd (entlast) tap4))
(command "_mirror" (entlast) "" "1280,900" "1280,901" "No")
(setq tap4 (ssadd (entlast) tap4))
(setq coords (list 
(list 1281.125 871.88) 
(list 1280.5625 871.88) 
(list 1280.5625 871.8903) 
(list 1280.5625 871.9006) 
(list 1280.5625 871.9108) 
(list 1280.5625 871.9211) 
(list 1280.5625 871.9314) 
(list 1280.5625 871.9417) 
(list 1280.5625 871.9519) 
(list 1280.5625 871.9622) 
(list 1280.5625 871.9725) 
(list 1280.5625 871.9828) 
(list 1280.5625 871.9931) 
(list 1280.5625 872.0033) 
(list 1280.5625 872.0136) 
(list 1280.5625 872.0239) 
(list 1280.5625 872.0342) 
(list 1280.5625 872.0444) 
(list 1280.5625 872.0547) 
(list 1280.5625 872.065) 
(list 1280.5625 872.0753) 
(list 1280.5625 872.0856) 
(list 1280.5625 872.0958) 
(list 1280.5625 872.1061) 
(list 1280.5625 872.1164) 
(list 1280.5625 872.1267) 
(list 1280.5625 872.1369) 
(list 1280.5625 872.1472) 
(list 1280.5625 872.1575) 
(list 1280.5625 872.1678) 
(list 1280.5625 872.1781) 
(list 1280.5625 872.1883) 
(list 1280.5625 872.1986) 
(list 1280.5625 872.2089) 
(list 1280.5625 872.2192) 
(list 1280.5625 872.2294) 
(list 1280.5625 872.2397) 
(list 1280.5625 872.25) 
(list 1281.125 872.25)))
(apply 'command (append '("pline") coords '("c")))
(setq tap4 (ssadd (entlast) tap4))
(command "_mirror" (entlast) "" "1280,900" "1280,901" "No")
(setq tap4 (ssadd (entlast) tap4))
(command "_block" "blktap4" "1280,900" tap4 "")
(command "_insert" "blktap4" "1280,900" "1" "1" "0")
(command "_insert" "blktap4" "1280,900" "1" "1" "180")
(setq uc4 nil)
(setq uc4 (ssadd))
(setq coords (list 
(list 0 -0.185) 
(list 0.135 -0.185) 
(list 0.135 -0.17472) 
(list 0.135 -0.16444) 
(list 0.135 -0.15417) 
(list 0.135 -0.14389) 
(list 0.135 -0.13361) 
(list 0.135 -0.12333) 
(list 0.135 -0.11306) 
(list 0.135 -0.10278) 
(list 0.135 -0.0925) 
(list 0.135 -0.082222) 
(list 0.135 -0.071944) 
(list 0.135 -0.061667) 
(list 0.135 -0.051389) 
(list 0.135 -0.041111) 
(list 0.135 -0.030833) 
(list 0.135 -0.020556) 
(list 0.135 -0.010278) 
(list 0.135 0) 
(list 0.135 0.010278) 
(list 0.135 0.020556) 
(list 0.135 0.030833) 
(list 0.135 0.041111) 
(list 0.135 0.051389) 
(list 0.135 0.061667) 
(list 0.135 0.071944) 
(list 0.135 0.082222) 
(list 0.135 0.0925) 
(list 0.135 0.10278) 
(list 0.135 0.11306) 
(list 0.135 0.12333) 
(list 0.135 0.13361) 
(list 0.135 0.14389) 
(list 0.135 0.15417) 
(list 0.135 0.16444) 
(list 0.135 0.17472) 
(list 0.135 0.185) 
(list 0 0.185)))
(apply 'command (append '("pline") coords '("c")))
(setq uc4 (ssadd (entlast) uc4))
(setq coords (list 
(list 1.125 -0.185) 
(list 0.5625 -0.185) 
(list 0.56044 -0.17472) 
(list 0.55433 -0.16444) 
(list 0.54435 -0.15417) 
(list 0.5308 -0.14389) 
(list 0.5141 -0.13361) 
(list 0.49475 -0.12333) 
(list 0.47334 -0.11306) 
(list 0.45053 -0.10278) 
(list 0.427 -0.0925) 
(list 0.40347 -0.082222) 
(list 0.38066 -0.071944) 
(list 0.35925 -0.061667) 
(list 0.3399 -0.051389) 
(list 0.3232 -0.041111) 
(list 0.30965 -0.030833) 
(list 0.29967 -0.020556) 
(list 0.29356 -0.010278) 
(list 0.2915 0) 
(list 0.29356 0.010278) 
(list 0.29967 0.020556) 
(list 0.30965 0.030833) 
(list 0.3232 0.041111) 
(list 0.3399 0.051389) 
(list 0.35925 0.061667) 
(list 0.38066 0.071944) 
(list 0.40347 0.082222) 
(list 0.427 0.0925) 
(list 0.45053 0.10278) 
(list 0.47334 0.11306) 
(list 0.49475 0.12333) 
(list 0.5141 0.13361) 
(list 0.5308 0.14389) 
(list 0.54435 0.15417) 
(list 0.55433 0.16444) 
(list 0.56044 0.17472) 
(list 0.5625 0.185) 
(list 1.125 0.185)))
(apply 'command (append '("pline") coords '("c")))
(setq uc4 (ssadd (entlast) uc4))
(command "_block" "blkuc4" "0,0.185" uc4 "")
(command "_insert" "blkuc4" "1280,872.62" "1" "1" "0")
(command "_insert" "blkuc4" "1280,872.25" "1" "1" "180")
(command "_insert" "blkuc4" "1280,872.99" "1" "1" "0")
(command "_insert" "blkuc4" "1280,872.62" "1" "1" "180")
(command "_insert" "blkuc4" "1280,873.36" "1" "1" "0")
(command "_insert" "blkuc4" "1280,872.99" "1" "1" "180")
(command "_insert" "blkuc4" "1280,873.73" "1" "1" "0")
(command "_insert" "blkuc4" "1280,873.36" "1" "1" "180")
(command "_insert" "blkuc4" "1280,874.1" "1" "1" "0")
(command "_insert" "blkuc4" "1280,873.73" "1" "1" "180")
(command "_insert" "blkuc4" "1280,874.47" "1" "1" "0")
(command "_insert" "blkuc4" "1280,874.1" "1" "1" "180")
(command "_insert" "blkuc4" "1280,874.84" "1" "1" "0")
(command "_insert" "blkuc4" "1280,874.47" "1" "1" "180")
(command "_insert" "blkuc4" "1280,875.21" "1" "1" "0")
(command "_insert" "blkuc4" "1280,874.84" "1" "1" "180")
(command "_insert" "blkuc4" "1280,875.58" "1" "1" "0")
(command "_insert" "blkuc4" "1280,875.21" "1" "1" "180")
(command "_insert" "blkuc4" "1280,875.95" "1" "1" "0")
(command "_insert" "blkuc4" "1280,875.58" "1" "1" "180")
(command "_insert" "blkuc4" "1280,876.32" "1" "1" "0")
(command "_insert" "blkuc4" "1280,875.95" "1" "1" "180")
(command "_insert" "blkuc4" "1280,876.69" "1" "1" "0")
(command "_insert" "blkuc4" "1280,876.32" "1" "1" "180")
(command "_insert" "blkuc4" "1280,877.06" "1" "1" "0")
(command "_insert" "blkuc4" "1280,876.69" "1" "1" "180")
(command "_insert" "blkuc4" "1280,877.43" "1" "1" "0")
(command "_insert" "blkuc4" "1280,877.06" "1" "1" "180")
(command "_insert" "blkuc4" "1280,877.8" "1" "1" "0")
(command "_insert" "blkuc4" "1280,877.43" "1" "1" "180")
(command "_insert" "blkuc4" "1280,878.17" "1" "1" "0")
(command "_insert" "blkuc4" "1280,877.8" "1" "1" "180")
(command "_insert" "blkuc4" "1280,878.54" "1" "1" "0")
(command "_insert" "blkuc4" "1280,878.17" "1" "1" "180")
(command "_insert" "blkuc4" "1280,878.91" "1" "1" "0")
(command "_insert" "blkuc4" "1280,878.54" "1" "1" "180")
(command "_insert" "blkuc4" "1280,879.28" "1" "1" "0")
(command "_insert" "blkuc4" "1280,878.91" "1" "1" "180")
(command "_insert" "blkuc4" "1280,879.65" "1" "1" "0")
(command "_insert" "blkuc4" "1280,879.28" "1" "1" "180")
(command "_insert" "blkuc4" "1280,880.02" "1" "1" "0")
(command "_insert" "blkuc4" "1280,879.65" "1" "1" "180")
(command "_insert" "blkuc4" "1280,880.39" "1" "1" "0")
(command "_insert" "blkuc4" "1280,880.02" "1" "1" "180")
(command "_insert" "blkuc4" "1280,880.76" "1" "1" "0")
(command "_insert" "blkuc4" "1280,880.39" "1" "1" "180")
(command "_insert" "blkuc4" "1280,881.13" "1" "1" "0")
(command "_insert" "blkuc4" "1280,880.76" "1" "1" "180")
(command "_insert" "blkuc4" "1280,881.5" "1" "1" "0")
(command "_insert" "blkuc4" "1280,881.13" "1" "1" "180")
(command "_insert" "blkuc4" "1280,881.87" "1" "1" "0")
(command "_insert" "blkuc4" "1280,881.5" "1" "1" "180")
(command "_insert" "blkuc4" "1280,882.24" "1" "1" "0")
(command "_insert" "blkuc4" "1280,881.87" "1" "1" "180")
(command "_insert" "blkuc4" "1280,882.61" "1" "1" "0")
(command "_insert" "blkuc4" "1280,882.24" "1" "1" "180")
(command "_insert" "blkuc4" "1280,882.98" "1" "1" "0")
(command "_insert" "blkuc4" "1280,882.61" "1" "1" "180")
(command "_insert" "blkuc4" "1280,883.35" "1" "1" "0")
(command "_insert" "blkuc4" "1280,882.98" "1" "1" "180")
(command "_insert" "blkuc4" "1280,883.72" "1" "1" "0")
(command "_insert" "blkuc4" "1280,883.35" "1" "1" "180")
(command "_insert" "blkuc4" "1280,884.09" "1" "1" "0")
(command "_insert" "blkuc4" "1280,883.72" "1" "1" "180")
(command "_insert" "blkuc4" "1280,884.46" "1" "1" "0")
(command "_insert" "blkuc4" "1280,884.09" "1" "1" "180")
(command "_insert" "blkuc4" "1280,884.83" "1" "1" "0")
(command "_insert" "blkuc4" "1280,884.46" "1" "1" "180")
(command "_insert" "blkuc4" "1280,885.2" "1" "1" "0")
(command "_insert" "blkuc4" "1280,884.83" "1" "1" "180")
(command "_insert" "blkuc4" "1280,885.57" "1" "1" "0")
(command "_insert" "blkuc4" "1280,885.2" "1" "1" "180")
(command "_insert" "blkuc4" "1280,885.94" "1" "1" "0")
(command "_insert" "blkuc4" "1280,885.57" "1" "1" "180")
(command "_insert" "blkuc4" "1280,886.31" "1" "1" "0")
(command "_insert" "blkuc4" "1280,885.94" "1" "1" "180")
(command "_insert" "blkuc4" "1280,886.68" "1" "1" "0")
(command "_insert" "blkuc4" "1280,886.31" "1" "1" "180")
(command "_insert" "blkuc4" "1280,887.05" "1" "1" "0")
(command "_insert" "blkuc4" "1280,886.68" "1" "1" "180")
(command "_insert" "blkuc4" "1280,887.42" "1" "1" "0")
(command "_insert" "blkuc4" "1280,887.05" "1" "1" "180")
(command "_insert" "blkuc4" "1280,887.79" "1" "1" "0")
(command "_insert" "blkuc4" "1280,887.42" "1" "1" "180")
(command "_insert" "blkuc4" "1280,888.16" "1" "1" "0")
(command "_insert" "blkuc4" "1280,887.79" "1" "1" "180")
(command "_insert" "blkuc4" "1280,888.53" "1" "1" "0")
(command "_insert" "blkuc4" "1280,888.16" "1" "1" "180")
(command "_insert" "blkuc4" "1280,888.9" "1" "1" "0")
(command "_insert" "blkuc4" "1280,888.53" "1" "1" "180")
(command "_insert" "blkuc4" "1280,889.27" "1" "1" "0")
(command "_insert" "blkuc4" "1280,888.9" "1" "1" "180")
(command "_insert" "blkuc4" "1280,889.64" "1" "1" "0")
(command "_insert" "blkuc4" "1280,889.27" "1" "1" "180")
(command "_insert" "blkuc4" "1280,890.01" "1" "1" "0")
(command "_insert" "blkuc4" "1280,889.64" "1" "1" "180")
(command "_insert" "blkuc4" "1280,890.38" "1" "1" "0")
(command "_insert" "blkuc4" "1280,890.01" "1" "1" "180")
(command "_insert" "blkuc4" "1280,890.75" "1" "1" "0")
(command "_insert" "blkuc4" "1280,890.38" "1" "1" "180")
(command "_insert" "blkuc4" "1280,891.12" "1" "1" "0")
(command "_insert" "blkuc4" "1280,890.75" "1" "1" "180")
(command "_insert" "blkuc4" "1280,891.49" "1" "1" "0")
(command "_insert" "blkuc4" "1280,891.12" "1" "1" "180")
(command "_insert" "blkuc4" "1280,891.86" "1" "1" "0")
(command "_insert" "blkuc4" "1280,891.49" "1" "1" "180")
(command "_insert" "blkuc4" "1280,892.23" "1" "1" "0")
(command "_insert" "blkuc4" "1280,891.86" "1" "1" "180")
(command "_insert" "blkuc4" "1280,892.6" "1" "1" "0")
(command "_insert" "blkuc4" "1280,892.23" "1" "1" "180")
(command "_insert" "blkuc4" "1280,892.97" "1" "1" "0")
(command "_insert" "blkuc4" "1280,892.6" "1" "1" "180")
(command "_insert" "blkuc4" "1280,893.34" "1" "1" "0")
(command "_insert" "blkuc4" "1280,892.97" "1" "1" "180")
(command "_insert" "blkuc4" "1280,893.71" "1" "1" "0")
(command "_insert" "blkuc4" "1280,893.34" "1" "1" "180")
(command "_insert" "blkuc4" "1280,894.08" "1" "1" "0")
(command "_insert" "blkuc4" "1280,893.71" "1" "1" "180")
(command "_insert" "blkuc4" "1280,894.45" "1" "1" "0")
(command "_insert" "blkuc4" "1280,894.08" "1" "1" "180")
(command "_insert" "blkuc4" "1280,894.82" "1" "1" "0")
(command "_insert" "blkuc4" "1280,894.45" "1" "1" "180")
(command "_insert" "blkuc4" "1280,895.19" "1" "1" "0")
(command "_insert" "blkuc4" "1280,894.82" "1" "1" "180")
(command "_insert" "blkuc4" "1280,895.56" "1" "1" "0")
(command "_insert" "blkuc4" "1280,895.19" "1" "1" "180")
(command "_insert" "blkuc4" "1280,895.93" "1" "1" "0")
(command "_insert" "blkuc4" "1280,895.56" "1" "1" "180")
(command "_insert" "blkuc4" "1280,896.3" "1" "1" "0")
(command "_insert" "blkuc4" "1280,895.93" "1" "1" "180")
(command "_insert" "blkuc4" "1280,896.67" "1" "1" "0")
(command "_insert" "blkuc4" "1280,896.3" "1" "1" "180")
(command "_insert" "blkuc4" "1280,897.04" "1" "1" "0")
(command "_insert" "blkuc4" "1280,896.67" "1" "1" "180")
(command "_insert" "blkuc4" "1280,897.41" "1" "1" "0")
(command "_insert" "blkuc4" "1280,897.04" "1" "1" "180")
(command "_insert" "blkuc4" "1280,897.78" "1" "1" "0")
(command "_insert" "blkuc4" "1280,897.41" "1" "1" "180")
(command "_insert" "blkuc4" "1280,898.15" "1" "1" "0")
(command "_insert" "blkuc4" "1280,897.78" "1" "1" "180")
(command "_insert" "blkuc4" "1280,898.52" "1" "1" "0")
(command "_insert" "blkuc4" "1280,898.15" "1" "1" "180")
(command "_insert" "blkuc4" "1280,898.89" "1" "1" "0")
(command "_insert" "blkuc4" "1280,898.52" "1" "1" "180")
(command "_insert" "blkuc4" "1280,899.26" "1" "1" "0")
(command "_insert" "blkuc4" "1280,898.89" "1" "1" "180")
(command "_insert" "blkuc4" "1280,899.63" "1" "1" "0")
(command "_insert" "blkuc4" "1280,899.26" "1" "1" "180")
(command "_insert" "blkuc4" "1280,900" "1" "1" "0")
(command "_insert" "blkuc4" "1280,899.63" "1" "1" "180")
(command "_insert" "blkuc4" "1280,900.37" "1" "1" "0")
(command "_insert" "blkuc4" "1280,900" "1" "1" "180")
(command "_insert" "blkuc4" "1280,900.74" "1" "1" "0")
(command "_insert" "blkuc4" "1280,900.37" "1" "1" "180")
(command "_insert" "blkuc4" "1280,901.11" "1" "1" "0")
(command "_insert" "blkuc4" "1280,900.74" "1" "1" "180")
(command "_insert" "blkuc4" "1280,901.48" "1" "1" "0")
(command "_insert" "blkuc4" "1280,901.11" "1" "1" "180")
(command "_insert" "blkuc4" "1280,901.85" "1" "1" "0")
(command "_insert" "blkuc4" "1280,901.48" "1" "1" "180")
(command "_insert" "blkuc4" "1280,902.22" "1" "1" "0")
(command "_insert" "blkuc4" "1280,901.85" "1" "1" "180")
(command "_insert" "blkuc4" "1280,902.59" "1" "1" "0")
(command "_insert" "blkuc4" "1280,902.22" "1" "1" "180")
(command "_insert" "blkuc4" "1280,902.96" "1" "1" "0")
(command "_insert" "blkuc4" "1280,902.59" "1" "1" "180")
(command "_insert" "blkuc4" "1280,903.33" "1" "1" "0")
(command "_insert" "blkuc4" "1280,902.96" "1" "1" "180")
(command "_insert" "blkuc4" "1280,903.7" "1" "1" "0")
(command "_insert" "blkuc4" "1280,903.33" "1" "1" "180")
(command "_insert" "blkuc4" "1280,904.07" "1" "1" "0")
(command "_insert" "blkuc4" "1280,903.7" "1" "1" "180")
(command "_insert" "blkuc4" "1280,904.44" "1" "1" "0")
(command "_insert" "blkuc4" "1280,904.07" "1" "1" "180")
(command "_insert" "blkuc4" "1280,904.81" "1" "1" "0")
(command "_insert" "blkuc4" "1280,904.44" "1" "1" "180")
(command "_insert" "blkuc4" "1280,905.18" "1" "1" "0")
(command "_insert" "blkuc4" "1280,904.81" "1" "1" "180")
(command "_insert" "blkuc4" "1280,905.55" "1" "1" "0")
(command "_insert" "blkuc4" "1280,905.18" "1" "1" "180")
(command "_insert" "blkuc4" "1280,905.92" "1" "1" "0")
(command "_insert" "blkuc4" "1280,905.55" "1" "1" "180")
(command "_insert" "blkuc4" "1280,906.29" "1" "1" "0")
(command "_insert" "blkuc4" "1280,905.92" "1" "1" "180")
(command "_insert" "blkuc4" "1280,906.66" "1" "1" "0")
(command "_insert" "blkuc4" "1280,906.29" "1" "1" "180")
(command "_insert" "blkuc4" "1280,907.03" "1" "1" "0")
(command "_insert" "blkuc4" "1280,906.66" "1" "1" "180")
(command "_insert" "blkuc4" "1280,907.4" "1" "1" "0")
(command "_insert" "blkuc4" "1280,907.03" "1" "1" "180")
(command "_insert" "blkuc4" "1280,907.77" "1" "1" "0")
(command "_insert" "blkuc4" "1280,907.4" "1" "1" "180")
(command "_insert" "blkuc4" "1280,908.14" "1" "1" "0")
(command "_insert" "blkuc4" "1280,907.77" "1" "1" "180")
(command "_insert" "blkuc4" "1280,908.51" "1" "1" "0")
(command "_insert" "blkuc4" "1280,908.14" "1" "1" "180")
(command "_insert" "blkuc4" "1280,908.88" "1" "1" "0")
(command "_insert" "blkuc4" "1280,908.51" "1" "1" "180")
(command "_insert" "blkuc4" "1280,909.25" "1" "1" "0")
(command "_insert" "blkuc4" "1280,908.88" "1" "1" "180")
(command "_insert" "blkuc4" "1280,909.62" "1" "1" "0")
(command "_insert" "blkuc4" "1280,909.25" "1" "1" "180")
(command "_insert" "blkuc4" "1280,909.99" "1" "1" "0")
(command "_insert" "blkuc4" "1280,909.62" "1" "1" "180")
(command "_insert" "blkuc4" "1280,910.36" "1" "1" "0")
(command "_insert" "blkuc4" "1280,909.99" "1" "1" "180")
(command "_insert" "blkuc4" "1280,910.73" "1" "1" "0")
(command "_insert" "blkuc4" "1280,910.36" "1" "1" "180")
(command "_insert" "blkuc4" "1280,911.1" "1" "1" "0")
(command "_insert" "blkuc4" "1280,910.73" "1" "1" "180")
(command "_insert" "blkuc4" "1280,911.47" "1" "1" "0")
(command "_insert" "blkuc4" "1280,911.1" "1" "1" "180")
(command "_insert" "blkuc4" "1280,911.84" "1" "1" "0")
(command "_insert" "blkuc4" "1280,911.47" "1" "1" "180")
(command "_insert" "blkuc4" "1280,912.21" "1" "1" "0")
(command "_insert" "blkuc4" "1280,911.84" "1" "1" "180")
(command "_insert" "blkuc4" "1280,912.58" "1" "1" "0")
(command "_insert" "blkuc4" "1280,912.21" "1" "1" "180")
(command "_insert" "blkuc4" "1280,912.95" "1" "1" "0")
(command "_insert" "blkuc4" "1280,912.58" "1" "1" "180")
(command "_insert" "blkuc4" "1280,913.32" "1" "1" "0")
(command "_insert" "blkuc4" "1280,912.95" "1" "1" "180")
(command "_insert" "blkuc4" "1280,913.69" "1" "1" "0")
(command "_insert" "blkuc4" "1280,913.32" "1" "1" "180")
(command "_insert" "blkuc4" "1280,914.06" "1" "1" "0")
(command "_insert" "blkuc4" "1280,913.69" "1" "1" "180")
(command "_insert" "blkuc4" "1280,914.43" "1" "1" "0")
(command "_insert" "blkuc4" "1280,914.06" "1" "1" "180")
(command "_insert" "blkuc4" "1280,914.8" "1" "1" "0")
(command "_insert" "blkuc4" "1280,914.43" "1" "1" "180")
(command "_insert" "blkuc4" "1280,915.17" "1" "1" "0")
(command "_insert" "blkuc4" "1280,914.8" "1" "1" "180")
(command "_insert" "blkuc4" "1280,915.54" "1" "1" "0")
(command "_insert" "blkuc4" "1280,915.17" "1" "1" "180")
(command "_insert" "blkuc4" "1280,915.91" "1" "1" "0")
(command "_insert" "blkuc4" "1280,915.54" "1" "1" "180")
(command "_insert" "blkuc4" "1280,916.28" "1" "1" "0")
(command "_insert" "blkuc4" "1280,915.91" "1" "1" "180")
(command "_insert" "blkuc4" "1280,916.65" "1" "1" "0")
(command "_insert" "blkuc4" "1280,916.28" "1" "1" "180")
(command "_insert" "blkuc4" "1280,917.02" "1" "1" "0")
(command "_insert" "blkuc4" "1280,916.65" "1" "1" "180")
(command "_insert" "blkuc4" "1280,917.39" "1" "1" "0")
(command "_insert" "blkuc4" "1280,917.02" "1" "1" "180")
(command "_insert" "blkuc4" "1280,917.76" "1" "1" "0")
(command "_insert" "blkuc4" "1280,917.39" "1" "1" "180")
(command "_insert" "blkuc4" "1280,918.13" "1" "1" "0")
(command "_insert" "blkuc4" "1280,917.76" "1" "1" "180")
(command "_insert" "blkuc4" "1280,918.5" "1" "1" "0")
(command "_insert" "blkuc4" "1280,918.13" "1" "1" "180")
(command "_insert" "blkuc4" "1280,918.87" "1" "1" "0")
(command "_insert" "blkuc4" "1280,918.5" "1" "1" "180")
(command "_insert" "blkuc4" "1280,919.24" "1" "1" "0")
(command "_insert" "blkuc4" "1280,918.87" "1" "1" "180")
(command "_insert" "blkuc4" "1280,919.61" "1" "1" "0")
(command "_insert" "blkuc4" "1280,919.24" "1" "1" "180")
(command "_insert" "blkuc4" "1280,919.98" "1" "1" "0")
(command "_insert" "blkuc4" "1280,919.61" "1" "1" "180")
(command "_insert" "blkuc4" "1280,920.35" "1" "1" "0")
(command "_insert" "blkuc4" "1280,919.98" "1" "1" "180")
(command "_insert" "blkuc4" "1280,920.72" "1" "1" "0")
(command "_insert" "blkuc4" "1280,920.35" "1" "1" "180")
(command "_insert" "blkuc4" "1280,921.09" "1" "1" "0")
(command "_insert" "blkuc4" "1280,920.72" "1" "1" "180")
(command "_insert" "blkuc4" "1280,921.46" "1" "1" "0")
(command "_insert" "blkuc4" "1280,921.09" "1" "1" "180")
(command "_insert" "blkuc4" "1280,921.83" "1" "1" "0")
(command "_insert" "blkuc4" "1280,921.46" "1" "1" "180")
(command "_insert" "blkuc4" "1280,922.2" "1" "1" "0")
(command "_insert" "blkuc4" "1280,921.83" "1" "1" "180")
(command "_insert" "blkuc4" "1280,922.57" "1" "1" "0")
(command "_insert" "blkuc4" "1280,922.2" "1" "1" "180")
(command "_insert" "blkuc4" "1280,922.94" "1" "1" "0")
(command "_insert" "blkuc4" "1280,922.57" "1" "1" "180")
(command "_insert" "blkuc4" "1280,923.31" "1" "1" "0")
(command "_insert" "blkuc4" "1280,922.94" "1" "1" "180")
(command "_insert" "blkuc4" "1280,923.68" "1" "1" "0")
(command "_insert" "blkuc4" "1280,923.31" "1" "1" "180")
(command "_insert" "blkuc4" "1280,924.05" "1" "1" "0")
(command "_insert" "blkuc4" "1280,923.68" "1" "1" "180")
(command "_insert" "blkuc4" "1280,924.42" "1" "1" "0")
(command "_insert" "blkuc4" "1280,924.05" "1" "1" "180")
(command "_insert" "blkuc4" "1280,924.79" "1" "1" "0")
(command "_insert" "blkuc4" "1280,924.42" "1" "1" "180")
(command "_insert" "blkuc4" "1280,925.16" "1" "1" "0")
(command "_insert" "blkuc4" "1280,924.79" "1" "1" "180")
(command "_insert" "blkuc4" "1280,925.53" "1" "1" "0")
(command "_insert" "blkuc4" "1280,925.16" "1" "1" "180")
(command "_insert" "blkuc4" "1280,925.9" "1" "1" "0")
(command "_insert" "blkuc4" "1280,925.53" "1" "1" "180")
(command "_insert" "blkuc4" "1280,926.27" "1" "1" "0")
(command "_insert" "blkuc4" "1280,925.9" "1" "1" "180")
(command "_insert" "blkuc4" "1280,926.64" "1" "1" "0")
(command "_insert" "blkuc4" "1280,926.27" "1" "1" "180")
(command "_insert" "blkuc4" "1280,927.01" "1" "1" "0")
(command "_insert" "blkuc4" "1280,926.64" "1" "1" "180")
(command "_insert" "blkuc4" "1280,927.38" "1" "1" "0")
(command "_insert" "blkuc4" "1280,927.01" "1" "1" "180")
(command "_insert" "blkuc4" "1280,927.75" "1" "1" "0")
(command "_insert" "blkuc4" "1280,927.38" "1" "1" "180")
(command "_layer" "set" "phccover" "")
(command "_rectangle" "1278.875,933.3" "1281.125,866.7")
(command "_layer" "set" "nitride" "")
(setq phc4 currobj)
(command "_layer" "set" "cover" "")
(command "_rectangle" "1278.875,836.7" "1281.125,963.3")
(command "_layer" "set" "nitride" "")
(command "_layer" "set" "text" "")
(command "_circle" "1277.925,846.7" "0.075")
(command "_circle" "1277.55,846.7" "0.15")
(command "_circle" "1277.175,846.7" "0.075")
(command "_circle" "1276.8,846.7" "0.15")
(command "_circle" "1277.925,848.7" "0.075")
(command "_circle" "1277.55,848.7" "0.075")
(command "_circle" "1277.175,848.7" "0.15")
(command "_circle" "1276.8,848.7" "0.15")
(command "_circle" "1277.925,850.7" "0.075")
(command "_circle" "1277.55,850.7" "0.15")
(command "_circle" "1277.175,850.7" "0.15")
(command "_circle" "1276.8,850.7" "0.15")
(command "_circle" "1277.925,852.7" "0.075")
(command "_circle" "1277.55,852.7" "0.075")
(command "_circle" "1277.175,852.7" "0.075")
(command "_circle" "1276.8,852.7" "0.075")
(command "_circle" "1276.425,852.7" "0.15")
(command "_circle" "1277.925,854.7" "0.075")
(command "_circle" "1277.55,854.7" "0.15")
(command "_circle" "1277.175,854.7" "0.075")
(command "_circle" "1276.8,854.7" "0.075")
(command "_circle" "1276.425,854.7" "0.15")
(command "_circle" "1277.925,856.7" "0.075")
(command "_circle" "1277.55,856.7" "0.075")
(command "_circle" "1277.175,856.7" "0.15")
(command "_circle" "1276.8,856.7" "0.075")
(command "_circle" "1276.425,856.7" "0.15")
(command "_circle" "1277.925,858.7" "0.075")
(command "_circle" "1277.55,858.7" "0.15")
(command "_circle" "1277.175,858.7" "0.15")
(command "_circle" "1276.8,858.7" "0.075")
(command "_circle" "1276.425,858.7" "0.15")
(command "_circle" "1277.925,860.7" "0.075")
(command "_circle" "1277.55,860.7" "0.075")
(command "_circle" "1277.175,860.7" "0.075")
(command "_circle" "1276.8,860.7" "0.15")
(command "_circle" "1276.425,860.7" "0.15")
(command "_circle" "1277.925,862.7" "0.075")
(command "_circle" "1277.55,862.7" "0.15")
(command "_circle" "1277.175,862.7" "0.075")
(command "_circle" "1276.8,862.7" "0.15")
(command "_circle" "1276.425,862.7" "0.15")
(command "_circle" "1277.925,864.7" "0.075")
(command "_circle" "1277.55,864.7" "0.075")
(command "_circle" "1277.175,864.7" "0.15")
(command "_circle" "1276.8,864.7" "0.15")
(command "_circle" "1276.425,864.7" "0.15")
(command "_circle" "1277.925,866.7" "0.075")
(command "_circle" "1277.55,866.7" "0.15")
(command "_circle" "1277.175,866.7" "0.15")
(command "_circle" "1276.8,866.7" "0.15")
(command "_circle" "1276.425,866.7" "0.15")
(command "_circle" "1277.925,868.7" "0.075")
(command "_circle" "1277.55,868.7" "0.075")
(command "_circle" "1277.175,868.7" "0.075")
(command "_circle" "1276.8,868.7" "0.075")
(command "_circle" "1276.425,868.7" "0.075")
(command "_circle" "1276.05,868.7" "0.15")
(command "_circle" "1277.925,870.7" "0.075")
(command "_circle" "1277.55,870.7" "0.15")
(command "_circle" "1277.175,870.7" "0.075")
(command "_circle" "1276.8,870.7" "0.075")
(command "_circle" "1276.425,870.7" "0.075")
(command "_circle" "1276.05,870.7" "0.15")
(command "_circle" "1277.925,872.7" "0.075")
(command "_circle" "1277.55,872.7" "0.075")
(command "_circle" "1277.175,872.7" "0.15")
(command "_circle" "1276.8,872.7" "0.075")
(command "_circle" "1276.425,872.7" "0.075")
(command "_circle" "1276.05,872.7" "0.15")
(command "_circle" "1277.925,874.7" "0.075")
(command "_circle" "1277.55,874.7" "0.15")
(command "_circle" "1277.175,874.7" "0.15")
(command "_circle" "1276.8,874.7" "0.075")
(command "_circle" "1276.425,874.7" "0.075")
(command "_circle" "1276.05,874.7" "0.15")
(command "_circle" "1277.925,876.7" "0.075")
(command "_circle" "1277.55,876.7" "0.075")
(command "_circle" "1277.175,876.7" "0.075")
(command "_circle" "1276.8,876.7" "0.15")
(command "_circle" "1276.425,876.7" "0.075")
(command "_circle" "1276.05,876.7" "0.15")
(command "_circle" "1277.925,878.7" "0.075")
(command "_circle" "1277.55,878.7" "0.15")
(command "_circle" "1277.175,878.7" "0.075")
(command "_circle" "1276.8,878.7" "0.15")
(command "_circle" "1276.425,878.7" "0.075")
(command "_circle" "1276.05,878.7" "0.15")
(command "_circle" "1277.925,880.7" "0.075")
(command "_circle" "1277.55,880.7" "0.075")
(command "_circle" "1277.175,880.7" "0.15")
(command "_circle" "1276.8,880.7" "0.15")
(command "_circle" "1276.425,880.7" "0.075")
(command "_circle" "1276.05,880.7" "0.15")
(command "_circle" "1277.925,882.7" "0.075")
(command "_circle" "1277.55,882.7" "0.15")
(command "_circle" "1277.175,882.7" "0.15")
(command "_circle" "1276.8,882.7" "0.15")
(command "_circle" "1276.425,882.7" "0.075")
(command "_circle" "1276.05,882.7" "0.15")
(command "_circle" "1277.925,884.7" "0.075")
(command "_circle" "1277.55,884.7" "0.075")
(command "_circle" "1277.175,884.7" "0.075")
(command "_circle" "1276.8,884.7" "0.075")
(command "_circle" "1276.425,884.7" "0.15")
(command "_circle" "1276.05,884.7" "0.15")
(command "_circle" "1277.925,886.7" "0.075")
(command "_circle" "1277.55,886.7" "0.15")
(command "_circle" "1277.175,886.7" "0.075")
(command "_circle" "1276.8,886.7" "0.075")
(command "_circle" "1276.425,886.7" "0.15")
(command "_circle" "1276.05,886.7" "0.15")
(command "_circle" "1277.925,888.7" "0.075")
(command "_circle" "1277.55,888.7" "0.075")
(command "_circle" "1277.175,888.7" "0.15")
(command "_circle" "1276.8,888.7" "0.075")
(command "_circle" "1276.425,888.7" "0.15")
(command "_circle" "1276.05,888.7" "0.15")
(command "_circle" "1277.925,890.7" "0.075")
(command "_circle" "1277.55,890.7" "0.15")
(command "_circle" "1277.175,890.7" "0.15")
(command "_circle" "1276.8,890.7" "0.075")
(command "_circle" "1276.425,890.7" "0.15")
(command "_circle" "1276.05,890.7" "0.15")
(command "_circle" "1277.925,892.7" "0.075")
(command "_circle" "1277.55,892.7" "0.075")
(command "_circle" "1277.175,892.7" "0.075")
(command "_circle" "1276.8,892.7" "0.15")
(command "_circle" "1276.425,892.7" "0.15")
(command "_circle" "1276.05,892.7" "0.15")
(command "_circle" "1277.925,894.7" "0.075")
(command "_circle" "1277.55,894.7" "0.15")
(command "_circle" "1277.175,894.7" "0.075")
(command "_circle" "1276.8,894.7" "0.15")
(command "_circle" "1276.425,894.7" "0.15")
(command "_circle" "1276.05,894.7" "0.15")
(command "_circle" "1277.925,896.7" "0.075")
(command "_circle" "1277.55,896.7" "0.075")
(command "_circle" "1277.175,896.7" "0.15")
(command "_circle" "1276.8,896.7" "0.15")
(command "_circle" "1276.425,896.7" "0.15")
(command "_circle" "1276.05,896.7" "0.15")
(command "_circle" "1277.925,898.7" "0.075")
(command "_circle" "1277.55,898.7" "0.15")
(command "_circle" "1277.175,898.7" "0.15")
(command "_circle" "1276.8,898.7" "0.15")
(command "_circle" "1276.425,898.7" "0.15")
(command "_circle" "1276.05,898.7" "0.15")
(command "_circle" "1277.925,900.7" "0.075")
(command "_circle" "1277.55,900.7" "0.075")
(command "_circle" "1277.175,900.7" "0.075")
(command "_circle" "1276.8,900.7" "0.075")
(command "_circle" "1276.425,900.7" "0.075")
(command "_circle" "1276.05,900.7" "0.075")
(command "_circle" "1275.675,900.7" "0.15")
(command "_circle" "1277.925,902.7" "0.075")
(command "_circle" "1277.55,902.7" "0.15")
(command "_circle" "1277.175,902.7" "0.075")
(command "_circle" "1276.8,902.7" "0.075")
(command "_circle" "1276.425,902.7" "0.075")
(command "_circle" "1276.05,902.7" "0.075")
(command "_circle" "1275.675,902.7" "0.15")
(command "_circle" "1277.925,904.7" "0.075")
(command "_circle" "1277.55,904.7" "0.075")
(command "_circle" "1277.175,904.7" "0.15")
(command "_circle" "1276.8,904.7" "0.075")
(command "_circle" "1276.425,904.7" "0.075")
(command "_circle" "1276.05,904.7" "0.075")
(command "_circle" "1275.675,904.7" "0.15")
(command "_circle" "1277.925,906.7" "0.075")
(command "_circle" "1277.55,906.7" "0.15")
(command "_circle" "1277.175,906.7" "0.15")
(command "_circle" "1276.8,906.7" "0.075")
(command "_circle" "1276.425,906.7" "0.075")
(command "_circle" "1276.05,906.7" "0.075")
(command "_circle" "1275.675,906.7" "0.15")
(command "_circle" "1277.925,908.7" "0.075")
(command "_circle" "1277.55,908.7" "0.075")
(command "_circle" "1277.175,908.7" "0.075")
(command "_circle" "1276.8,908.7" "0.15")
(command "_circle" "1276.425,908.7" "0.075")
(command "_circle" "1276.05,908.7" "0.075")
(command "_circle" "1275.675,908.7" "0.15")
(command "_circle" "1277.925,910.7" "0.075")
(command "_circle" "1277.55,910.7" "0.15")
(command "_circle" "1277.175,910.7" "0.075")
(command "_circle" "1276.8,910.7" "0.15")
(command "_circle" "1276.425,910.7" "0.075")
(command "_circle" "1276.05,910.7" "0.075")
(command "_circle" "1275.675,910.7" "0.15")
(command "_circle" "1277.925,912.7" "0.075")
(command "_circle" "1277.55,912.7" "0.075")
(command "_circle" "1277.175,912.7" "0.15")
(command "_circle" "1276.8,912.7" "0.15")
(command "_circle" "1276.425,912.7" "0.075")
(command "_circle" "1276.05,912.7" "0.075")
(command "_circle" "1275.675,912.7" "0.15")
(command "_circle" "1277.925,914.7" "0.075")
(command "_circle" "1277.55,914.7" "0.15")
(command "_circle" "1277.175,914.7" "0.15")
(command "_circle" "1276.8,914.7" "0.15")
(command "_circle" "1276.425,914.7" "0.075")
(command "_circle" "1276.05,914.7" "0.075")
(command "_circle" "1275.675,914.7" "0.15")
(command "_circle" "1277.925,916.7" "0.075")
(command "_circle" "1277.55,916.7" "0.075")
(command "_circle" "1277.175,916.7" "0.075")
(command "_circle" "1276.8,916.7" "0.075")
(command "_circle" "1276.425,916.7" "0.15")
(command "_circle" "1276.05,916.7" "0.075")
(command "_circle" "1275.675,916.7" "0.15")
(command "_circle" "1277.925,918.7" "0.075")
(command "_circle" "1277.55,918.7" "0.15")
(command "_circle" "1277.175,918.7" "0.075")
(command "_circle" "1276.8,918.7" "0.075")
(command "_circle" "1276.425,918.7" "0.15")
(command "_circle" "1276.05,918.7" "0.075")
(command "_circle" "1275.675,918.7" "0.15")
(command "_circle" "1277.925,920.7" "0.075")
(command "_circle" "1277.55,920.7" "0.075")
(command "_circle" "1277.175,920.7" "0.15")
(command "_circle" "1276.8,920.7" "0.075")
(command "_circle" "1276.425,920.7" "0.15")
(command "_circle" "1276.05,920.7" "0.075")
(command "_circle" "1275.675,920.7" "0.15")
(command "_circle" "1277.925,922.7" "0.075")
(command "_circle" "1277.55,922.7" "0.15")
(command "_circle" "1277.175,922.7" "0.15")
(command "_circle" "1276.8,922.7" "0.075")
(command "_circle" "1276.425,922.7" "0.15")
(command "_circle" "1276.05,922.7" "0.075")
(command "_circle" "1275.675,922.7" "0.15")
(command "_circle" "1277.925,924.7" "0.075")
(command "_circle" "1277.55,924.7" "0.075")
(command "_circle" "1277.175,924.7" "0.075")
(command "_circle" "1276.8,924.7" "0.15")
(command "_circle" "1276.425,924.7" "0.15")
(command "_circle" "1276.05,924.7" "0.075")
(command "_circle" "1275.675,924.7" "0.15")
(command "_circle" "1277.925,926.7" "0.075")
(command "_circle" "1277.55,926.7" "0.15")
(command "_circle" "1277.175,926.7" "0.075")
(command "_circle" "1276.8,926.7" "0.15")
(command "_circle" "1276.425,926.7" "0.15")
(command "_circle" "1276.05,926.7" "0.075")
(command "_circle" "1275.675,926.7" "0.15")
(command "_circle" "1277.925,928.7" "0.075")
(command "_circle" "1277.55,928.7" "0.075")
(command "_circle" "1277.175,928.7" "0.15")
(command "_circle" "1276.8,928.7" "0.15")
(command "_circle" "1276.425,928.7" "0.15")
(command "_circle" "1276.05,928.7" "0.075")
(command "_circle" "1275.675,928.7" "0.15")
(command "_circle" "1277.925,930.7" "0.075")
(command "_circle" "1277.55,930.7" "0.15")
(command "_circle" "1277.175,930.7" "0.15")
(command "_circle" "1276.8,930.7" "0.15")
(command "_circle" "1276.425,930.7" "0.15")
(command "_circle" "1276.05,930.7" "0.075")
(command "_circle" "1275.675,930.7" "0.15")
(command "_circle" "1277.925,932.7" "0.075")
(command "_circle" "1277.55,932.7" "0.075")
(command "_circle" "1277.175,932.7" "0.075")
(command "_circle" "1276.8,932.7" "0.075")
(command "_circle" "1276.425,932.7" "0.075")
(command "_circle" "1276.05,932.7" "0.15")
(command "_circle" "1275.675,932.7" "0.15")
(command "_circle" "1277.925,934.7" "0.075")
(command "_circle" "1277.55,934.7" "0.15")
(command "_circle" "1277.175,934.7" "0.075")
(command "_circle" "1276.8,934.7" "0.075")
(command "_circle" "1276.425,934.7" "0.075")
(command "_circle" "1276.05,934.7" "0.15")
(command "_circle" "1275.675,934.7" "0.15")
(command "_circle" "1277.925,936.7" "0.075")
(command "_circle" "1277.55,936.7" "0.075")
(command "_circle" "1277.175,936.7" "0.15")
(command "_circle" "1276.8,936.7" "0.075")
(command "_circle" "1276.425,936.7" "0.075")
(command "_circle" "1276.05,936.7" "0.15")
(command "_circle" "1275.675,936.7" "0.15")
(command "_circle" "1277.925,938.7" "0.075")
(command "_circle" "1277.55,938.7" "0.15")
(command "_circle" "1277.175,938.7" "0.15")
(command "_circle" "1276.8,938.7" "0.075")
(command "_circle" "1276.425,938.7" "0.075")
(command "_circle" "1276.05,938.7" "0.15")
(command "_circle" "1275.675,938.7" "0.15")
(command "_circle" "1277.925,940.7" "0.075")
(command "_circle" "1277.55,940.7" "0.075")
(command "_circle" "1277.175,940.7" "0.075")
(command "_circle" "1276.8,940.7" "0.15")
(command "_circle" "1276.425,940.7" "0.075")
(command "_circle" "1276.05,940.7" "0.15")
(command "_circle" "1275.675,940.7" "0.15")
(command "_circle" "1277.925,942.7" "0.075")
(command "_circle" "1277.55,942.7" "0.15")
(command "_circle" "1277.175,942.7" "0.075")
(command "_circle" "1276.8,942.7" "0.15")
(command "_circle" "1276.425,942.7" "0.075")
(command "_circle" "1276.05,942.7" "0.15")
(command "_circle" "1275.675,942.7" "0.15")
(command "_circle" "1277.925,944.7" "0.075")
(command "_circle" "1277.55,944.7" "0.075")
(command "_circle" "1277.175,944.7" "0.15")
(command "_circle" "1276.8,944.7" "0.15")
(command "_circle" "1276.425,944.7" "0.075")
(command "_circle" "1276.05,944.7" "0.15")
(command "_circle" "1275.675,944.7" "0.15")
(command "_circle" "1277.925,946.7" "0.075")
(command "_circle" "1277.55,946.7" "0.15")
(command "_circle" "1277.175,946.7" "0.15")
(command "_circle" "1276.8,946.7" "0.15")
(command "_circle" "1276.425,946.7" "0.075")
(command "_circle" "1276.05,946.7" "0.15")
(command "_circle" "1275.675,946.7" "0.15")
(command "_circle" "1277.925,948.7" "0.075")
(command "_circle" "1277.55,948.7" "0.075")
(command "_circle" "1277.175,948.7" "0.075")
(command "_circle" "1276.8,948.7" "0.075")
(command "_circle" "1276.425,948.7" "0.15")
(command "_circle" "1276.05,948.7" "0.15")
(command "_circle" "1275.675,948.7" "0.15")
(command "_circle" "1277.925,950.7" "0.075")
(command "_circle" "1277.55,950.7" "0.15")
(command "_circle" "1277.175,950.7" "0.075")
(command "_circle" "1276.8,950.7" "0.075")
(command "_circle" "1276.425,950.7" "0.15")
(command "_circle" "1276.05,950.7" "0.15")
(command "_circle" "1275.675,950.7" "0.15")
(command "_circle" "1277.925,952.7" "0.075")
(command "_circle" "1277.55,952.7" "0.075")
(command "_circle" "1277.175,952.7" "0.15")
(command "_circle" "1276.8,952.7" "0.075")
(command "_circle" "1276.425,952.7" "0.15")
(command "_circle" "1276.05,952.7" "0.15")
(command "_circle" "1275.675,952.7" "0.15")
(command "_circle" "1277.925,954.7" "0.075")
(command "_circle" "1277.55,954.7" "0.15")
(command "_circle" "1277.175,954.7" "0.15")
(command "_circle" "1276.8,954.7" "0.075")
(command "_circle" "1276.425,954.7" "0.15")
(command "_circle" "1276.05,954.7" "0.15")
(command "_circle" "1275.675,954.7" "0.15")
(command "_circle" "1277.925,956.7" "0.075")
(command "_circle" "1277.55,956.7" "0.075")
(command "_circle" "1277.175,956.7" "0.075")
(command "_circle" "1276.8,956.7" "0.15")
(command "_circle" "1276.425,956.7" "0.15")
(command "_circle" "1276.05,956.7" "0.15")
(command "_circle" "1275.675,956.7" "0.15")
(command "_circle" "1277.925,958.7" "0.075")
(command "_circle" "1277.55,958.7" "0.15")
(command "_circle" "1277.175,958.7" "0.075")
(command "_circle" "1276.8,958.7" "0.15")
(command "_circle" "1276.425,958.7" "0.15")
(command "_circle" "1276.05,958.7" "0.15")
(command "_circle" "1275.675,958.7" "0.15")
(command "_circle" "1277.925,960.7" "0.075")
(command "_circle" "1277.55,960.7" "0.075")
(command "_circle" "1277.175,960.7" "0.15")
(command "_circle" "1276.8,960.7" "0.15")
(command "_circle" "1276.425,960.7" "0.15")
(command "_circle" "1276.05,960.7" "0.15")
(command "_circle" "1275.675,960.7" "0.15")
(command "_circle" "1277.925,962.7" "0.075")
(command "_circle" "1277.55,962.7" "0.15")
(command "_circle" "1277.175,962.7" "0.15")
(command "_circle" "1276.8,962.7" "0.15")
(command "_circle" "1276.425,962.7" "0.15")
(command "_circle" "1276.05,962.7" "0.15")
(command "_circle" "1275.675,962.7" "0.15")
(command "_layer" "set" "nitride" "")
(command "_layer" "set" "text" "")
(command-s "_text" "1266.875,963.3" "2" "-90" "a = 370 nm" )
(sssetfirst nil (ssget "_L"))
(if (not (numberp (vl-string-search "Mac" (getvar "platform")))) (c:txtexp))
(command "_layer" "set" "nitride" "")
(command "_layer" "set" "text" "")
(command-s "_text" "1263.875,963.3" "2" "-90" "gap = 270 nm" )
(sssetfirst nil (ssget "_L"))
(if (not (numberp (vl-string-search "Mac" (getvar "platform")))) (c:txtexp))
(command "_layer" "set" "nitride" "")
(command "_layer" "set" "text" "")
(command-s "_text" "1260.875,963.3" "2" "-90" "amplitude = 135.5 nm" )
(sssetfirst nil (ssget "_L"))
(if (not (numberp (vl-string-search "Mac" (getvar "platform")))) (c:txtexp))
(command "_layer" "set" "nitride" "")
(command "_layer" "set" "text" "")
(command-s "_text" "1257.875,963.3" "2" "-90" "start width = 280 nm" )
(sssetfirst nil (ssget "_L"))
(if (not (numberp (vl-string-search "Mac" (getvar "platform")))) (c:txtexp))
(command "_layer" "set" "nitride" "")
(command "_layer" "set" "text" "")
(command-s "_text" "1254.875,963.3" "2" "-90" "width = 292 nm" )
(sssetfirst nil (ssget "_L"))
(if (not (numberp (vl-string-search "Mac" (getvar "platform")))) (c:txtexp))
(command "_layer" "set" "nitride" "")
(command "_layer" "set" "text" "")
(command-s "_text" "1251.875,963.3" "2" "-90" "taper: 15" )
(sssetfirst nil (ssget "_L"))
(if (not (numberp (vl-string-search "Mac" (getvar "platform")))) (c:txtexp))
(command "_layer" "set" "nitride" "")
(command "_layer" "set" "text" "")
(command-s "_text" "1248.875,963.3" "2" "-90" "nominal: 150" )
(sssetfirst nil (ssget "_L"))
(if (not (numberp (vl-string-search "Mac" (getvar "platform")))) (c:txtexp))
(command "_layer" "set" "nitride" "")
(command "_layer" "set" "indicators" "")
(setq coords (list 
(list 1200.415 940) 
(list 1200.415 920) 
(list 1180.415 900) 
(list 1200.415 880) 
(list 1200.415 860) 
(list 1200.415 900) 
(list 1200.415 887.0711) 
(list 1187.4861 900) 
(list 1200.415 912.9289) 
(list 1200.415 900)))
(apply 'command (append '("pline") coords '("c")))
(command "._fillet" "radius" "1" "._fillet" "P" (entlast))
(setq coords (list 
(list 1359.585 940) 
(list 1359.585 920) 
(list 1379.585 900) 
(list 1359.585 880) 
(list 1359.585 860) 
(list 1359.585 900) 
(list 1359.585 887.0711) 
(list 1372.5139 900) 
(list 1359.585 912.9289) 
(list 1359.585 900)))
(apply 'command (append '("pline") coords '("c")))
(command "._fillet" "radius" "1" "._fillet" "P" (entlast))
(command "_layer" "set" "holes" "")
(command "_circle" "1198.0629,914.1124" "0.5")
(command "_circle" "1195.7109,911.7603" "0.5")
(command "_circle" "1193.3588,909.4083" "0.5")
(command "_circle" "1191.0067,907.0562" "0.5")
(command "_circle" "1188.6547,904.7041" "0.5")
(command "_circle" "1186.3026,902.3521" "0.5")
(command "_circle" "1183.9505,900" "0.5")
(command "_circle" "1186.3026,897.6479" "0.5")
(command "_circle" "1188.6547,895.2959" "0.5")
(command "_circle" "1191.0067,892.9438" "0.5")
(command "_circle" "1193.3588,890.5917" "0.5")
(command "_circle" "1195.7109,888.2397" "0.5")
(command "_circle" "1198.0629,885.8876" "0.5")
(command "_circle" "1361.9371,914.1124" "0.5")
(command "_circle" "1364.2891,911.7603" "0.5")
(command "_circle" "1366.6412,909.4083" "0.5")
(command "_circle" "1368.9933,907.0562" "0.5")
(command "_circle" "1371.3453,904.7041" "0.5")
(command "_circle" "1373.6974,902.3521" "0.5")
(command "_circle" "1376.0495,900" "0.5")
(command "_circle" "1373.6974,897.6479" "0.5")
(command "_circle" "1371.3453,895.2959" "0.5")
(command "_circle" "1368.9933,892.9438" "0.5")
(command "_circle" "1366.6412,890.5917" "0.5")
(command "_circle" "1364.2891,888.2397" "0.5")
(command "_circle" "1361.9371,885.8876" "0.5")
(command "_layer" "set" "nitride" "")
(command "_block" "blkcoupler4" "1280,900" coupler4 "")
(command "_insert" "blkcoupler4" "1280,900" "1" "1" "0")
(command "_insert" "blkcoupler4" "1280,900" "1" "1" "180")
(command "_block" "blksinglenanobeam4" "1280,900" singlenanobeam4 "")
(command "_insert" "blksinglenanobeam4" "1280,900" "1" "1" "0")
(command "_insert" "blksinglenanobeam4" "1280,900" "1" "1" "180")
(command "_block" "blkanglednodearray4" "1280,900" anglednodearray4 "")
(command "_insert" "blkanglednodearray4" "1280,900" "1" "1" "0")
(command "_insert" "blkanglednodearray4" "1280,900" "1" "1" "180")
(command "_block" "blkcooledsinglenanobeam4" "1280,900" cooledsinglenanobeam4 "")
(command "_insert" "blkcooledsinglenanobeam4" "1280,900" "1" "1" "0")
(command "_insert" "blkcooledsinglenanobeam4" "1280,900" "1" "1" "180")
(command "_block" "blkyjunction4" "1280,900" yjunction4 "")
(command "_insert" "blkyjunction4" "1280,900" "1" "1" "0")
(command "_insert" "blkyjunction4" "1280,900" "1" "1" "180")
; DRAWING BULGING VEE GROOVE
(command "_layer" "set" "vgroove" "")
(setq coords (list 
(list 1205.415 -605) 
(list 1205.415 0) 
(list 1205.415 0) 
(list 1205.415 1800) 
(list 1205.415 1800) 
(list 1205.415 2405) 
(list 1354.585 2405) 
(list 1354.585 1800) 
(list 1354.585 1800) 
(list 1354.585 0) 
(list 1354.585 0) 
(list 1354.585 -605)))
(apply 'command (append '("pline") coords '("c")))
(command "._fillet" "radius" "0" "._fillet" "P" (entlast))
(command "_layer" "set" "window" "")
(command "_rectangle" "1205.415,-1935" "1354.585,-600")
(command "_rectangle" "1205.415,2400" "1354.585,5300")
(command "_layer" "set" "grid" "")
(command "_rectangle" "1206.415,-1934" "1229.9433,-1909.2133")
(command "_array" "last" "" "R" "75" "3" "25.7867" "24.5283")
(command "_rectangle" "1281,-1934" "1304.5283,-1909.2133")
(command "_array" "last" "" "R" "75" "3" "25.7867" "24.5283")
(command "_rectangle" "1206.415,1" "1229.9433,25.7")
(command "_array" "last" "" "R" "70" "3" "25.7" "24.5283")
(command "_rectangle" "1281,1" "1304.5283,25.7")
(command "_array" "last" "" "R" "70" "3" "25.7" "24.5283")
(command "_rectangle" "1206.415,1801" "1229.9433,1825.9185")
(command "_array" "last" "" "R" "135" "3" "25.9185" "24.5283")
(command "_rectangle" "1281,1801" "1304.5283,1825.9185")
(command "_array" "last" "" "R" "135" "3" "25.9185" "24.5283")
(command "_layer" "set" "vgrooveFDA" "")
(command "_rectangle" "1354.585,-2233" "1205.415,-1933")
(command "_layer" "set" "nitride" "")
(command "_layer" "set" "holes" "")
(command "_circle" "1357.085,331.5" "0.5")
(command "_array" "last" "" "R" "379" "1" "3" "2.5")
(command "_circle" "1202.915,331.5" "0.5")
(command "_array" "last" "" "R" "379" "1" "3" "-2.5")
(command "_layer" "set" "nitride" "")
(command "_layer" "set" "window" "")
(command "_layer" "set" "window" "")
(command "_rectangle" "1359.585,0" "1520.415,1800")
(command "._fillet" "radius" "20" "._fillet" "P" (entlast))
(command "_layer" "set" "grid" "")
(command "_rectangle" "1360.585,1" "1382.4179,25.7")
(command "_array" "last" "" "R" "70" "7" "25.7" "22.8329")
(command "_layer" "set" "nitride" "")
; DRAWING REGION LAYER
(command "_layer" "set" "regionLayer4" "")
(command "_rectangle" "1200,-460" "1360,2260")
(command "_layer" "set" "nitride" "")
(setq coupler4 nil)
(setq singlenanobeam4 nil)
(setq anglednodearray4 nil)
(setq cooledsinglenanobeam4 nil)
(setq yjunction4 nil)
; DEVICE #5
(command "_layer" "set" "window" "")
(command "_circle" "1512.915,-415" "5")
(command "_circle" "1512.915,-402.5" "5")
(command "_circle" "1512.915,-390" "5")
(command "_circle" "1512.915,-377.5" "5")
(command "_circle" "1500.415,-415" "5")
(command "_layer" "set" "nitride" "")
(setq currobj nil)
(setq currobj (ssadd))
; DRAWING COUPLER
(setq coords (list 
(list 1600.0645 -415) 
(list 1600.0645 -413) 
(list 1673.585 -413) 
(list 1673.585 -413) 
(list 1673.9677 -413.0761) 
(list 1674.2921 -413.2929) 
(list 1674.5089 -413.6173) 
(list 1674.585 -414) 
(list 1674.585 -411.8) 
(list 1674.585 -411.8) 
(list 1674.5089 -412.1827) 
(list 1674.2921 -412.5071) 
(list 1673.9677 -412.7239) 
(list 1673.585 -412.8) 
(list 1600.0645 -412.8) 
(list 1600.0645 -410.8) 
(list 1599.9355 -410.8) 
(list 1599.9355 -412.8) 
(list 1526.415 -412.8) 
(list 1526.0323 -412.7239) 
(list 1525.7079 -412.5071) 
(list 1525.4911 -412.1827) 
(list 1525.415 -411.8) 
(list 1525.415 -411.8) 
(list 1525.415 -414) 
(list 1525.4911 -413.6173) 
(list 1525.7079 -413.2929) 
(list 1526.0323 -413.0761) 
(list 1526.415 -413) 
(list 1526.415 -413) 
(list 1599.9355 -413) 
(list 1599.9355 -415)))
(apply 'command (append '("pline") coords '("c")))
(setq currobj (ssadd (entlast) currobj))
(command "._fillet" "radius" "0.3" "._fillet" "P" (entlast))
(command "_layer" "set" "holes" "")
(command "_circle" "1600,-412.9" "0.113")
(setq currobj (ssadd (entlast) currobj))
(command "_layer" "set" "nitride" "")
(command "_layer" "set" "text" "")
(command "_circle" "1599.2,-415" "0.075")
(command "_circle" "1599.2,-414.7" "0.075")
(command "_circle" "1599.2,-414.4" "0.075")
(command "_circle" "1598.9,-415" "0.075")
(command "_circle" "1598.9,-414.7" "0.075")
(command "_circle" "1598.9,-414.4" "0.075")
(command "_circle" "1598.6,-415" "0.075")
(command "_circle" "1598.6,-414.7" "0.075")
(command "_circle" "1598.6,-414.4" "0.075")
(command "_layer" "set" "nitride" "")
(command "_layer" "set" "prebias" "")
(command "_rectangle" "1525.415,-414" "1674.585,-411.8")
(setq currobj (ssadd (entlast) currobj))
(command "_rectangle" "1599.9355,-415" "1600.0645,-410.8")
(setq currobj (ssadd (entlast) currobj))
(command "_layer" "set" "nitride" "")
(setq coupler5 currobj)
(setq currobj nil)
(setq currobj (ssadd))
; DRAWING SINGLE NANOBEAM
(setq coords (list 
(list 1600.0645 -410.8) 
(list 1600.0645 -409.1417) 
(list 1600.0645 -407.4833) 
(list 1600.0645 -405.825) 
(list 1600.0645 -404.1667) 
(list 1600.0645 -402.5083) 
(list 1600.0645 -400.85) 
(list 1600.0645 -399.1917) 
(list 1600.0645 -397.5333) 
(list 1600.0646 -395.875) 
(list 1600.0646 -394.2167) 
(list 1600.0646 -392.5583) 
(list 1600.0646 -390.9) 
(list 1600.0647 -389.2417) 
(list 1600.0647 -387.5833) 
(list 1600.0647 -385.925) 
(list 1600.0648 -384.2667) 
(list 1600.0648 -382.6083) 
(list 1600.0649 -380.95) 
(list 1600.065 -379.2917) 
(list 1600.0651 -377.6333) 
(list 1600.0651 -375.975) 
(list 1600.0652 -374.3167) 
(list 1600.0653 -372.6583) 
(list 1600.0655 -371) 
(list 1600.0656 -369.3417) 
(list 1600.0657 -367.6833) 
(list 1600.0659 -366.025) 
(list 1600.066 -364.3667) 
(list 1600.0662 -362.7083) 
(list 1600.0664 -361.05) 
(list 1600.0666 -359.3917) 
(list 1600.0668 -357.7333) 
(list 1600.067 -356.075) 
(list 1600.0672 -354.4167) 
(list 1600.0675 -352.7583) 
(list 1600.0678 -351.1) 
(list 1600.068 -349.4417) 
(list 1600.0683 -347.7833) 
(list 1600.0686 -346.125) 
(list 1600.069 -344.4667) 
(list 1600.0693 -342.8083) 
(list 1600.0697 -341.15) 
(list 1600.07 -339.4917) 
(list 1600.0704 -337.8333) 
(list 1600.0709 -336.175) 
(list 1600.0713 -334.5167) 
(list 1600.0717 -332.8583) 
(list 1600.0722 -331.2) 
(list 1600.0727 -329.5417) 
(list 1600.0732 -327.8833) 
(list 1600.0738 -326.225) 
(list 1600.0743 -324.5667) 
(list 1600.0749 -322.9083) 
(list 1600.0755 -321.25) 
(list 1600.0761 -319.5917) 
(list 1600.0767 -317.9333) 
(list 1600.0774 -316.275) 
(list 1600.0781 -314.6167) 
(list 1600.0788 -312.9583) 
(list 1600.0796 -311.3) 
(list 1600.0803 -309.6417) 
(list 1600.0811 -307.9833) 
(list 1600.0819 -306.325) 
(list 1600.0828 -304.6667) 
(list 1600.0837 -303.0083) 
(list 1600.0845 -301.35) 
(list 1600.0855 -299.6917) 
(list 1600.0864 -298.0333) 
(list 1600.0874 -296.375) 
(list 1600.0884 -294.7167) 
(list 1600.0895 -293.0583) 
(list 1600.0905 -291.4) 
(list 1600.0916 -289.7417) 
(list 1600.0928 -288.0833) 
(list 1600.0939 -286.425) 
(list 1600.0951 -284.7667) 
(list 1600.0963 -283.1083) 
(list 1600.0976 -281.45) 
(list 1600.0989 -279.7917) 
(list 1600.1002 -278.1333) 
(list 1600.1016 -276.475) 
(list 1600.1029 -274.8167) 
(list 1600.1044 -273.1583) 
(list 1600.1058 -271.5) 
(list 1600.1073 -269.8417) 
(list 1600.1089 -268.1833) 
(list 1600.1104 -266.525) 
(list 1600.112 -264.8667) 
(list 1600.1137 -263.2083) 
(list 1600.1153 -261.55) 
(list 1600.117 -259.8917) 
(list 1600.1188 -258.2333) 
(list 1600.1206 -256.575) 
(list 1600.1224 -254.9167) 
(list 1600.1243 -253.2583) 
(list 1600.1262 -251.6) 
(list 1600.1281 -249.9417) 
(list 1600.1301 -248.2833) 
(list 1600.1322 -246.625) 
(list 1600.1342 -244.9667) 
(list 1600.1363 -243.3083) 
(list 1600.1385 -241.65) 
(list 1600.1407 -239.9917) 
(list 1600.1429 -238.3333) 
(list 1600.1452 -236.675) 
(list 1600.1476 -235.0167) 
(list 1600.1499 -233.3583) 
(list 1600.1523 -231.7) 
(list 1600.1548 -230.0417) 
(list 1600.1573 -228.3833) 
(list 1600.1599 -226.725) 
(list 1600.1625 -225.0667) 
(list 1600.1651 -223.4083) 
(list 1600.1678 -221.75) 
(list 1600.1706 -220.0917) 
(list 1600.1733 -218.4333) 
(list 1600.1762 -216.775) 
(list 1600.1791 -215.1167) 
(list 1600.182 -213.4583) 
(list 1600.185 -211.8) 
(list 1599.815 -211.8) 
(list 1599.818 -213.4583) 
(list 1599.8209 -215.1167) 
(list 1599.8238 -216.775) 
(list 1599.8267 -218.4333) 
(list 1599.8294 -220.0917) 
(list 1599.8322 -221.75) 
(list 1599.8349 -223.4083) 
(list 1599.8375 -225.0667) 
(list 1599.8401 -226.725) 
(list 1599.8427 -228.3833) 
(list 1599.8452 -230.0417) 
(list 1599.8477 -231.7) 
(list 1599.8501 -233.3583) 
(list 1599.8524 -235.0167) 
(list 1599.8548 -236.675) 
(list 1599.8571 -238.3333) 
(list 1599.8593 -239.9917) 
(list 1599.8615 -241.65) 
(list 1599.8637 -243.3083) 
(list 1599.8658 -244.9667) 
(list 1599.8678 -246.625) 
(list 1599.8699 -248.2833) 
(list 1599.8719 -249.9417) 
(list 1599.8738 -251.6) 
(list 1599.8757 -253.2583) 
(list 1599.8776 -254.9167) 
(list 1599.8794 -256.575) 
(list 1599.8812 -258.2333) 
(list 1599.883 -259.8917) 
(list 1599.8847 -261.55) 
(list 1599.8863 -263.2083) 
(list 1599.888 -264.8667) 
(list 1599.8896 -266.525) 
(list 1599.8911 -268.1833) 
(list 1599.8927 -269.8417) 
(list 1599.8942 -271.5) 
(list 1599.8956 -273.1583) 
(list 1599.8971 -274.8167) 
(list 1599.8984 -276.475) 
(list 1599.8998 -278.1333) 
(list 1599.9011 -279.7917) 
(list 1599.9024 -281.45) 
(list 1599.9037 -283.1083) 
(list 1599.9049 -284.7667) 
(list 1599.9061 -286.425) 
(list 1599.9072 -288.0833) 
(list 1599.9084 -289.7417) 
(list 1599.9095 -291.4) 
(list 1599.9105 -293.0583) 
(list 1599.9116 -294.7167) 
(list 1599.9126 -296.375) 
(list 1599.9136 -298.0333) 
(list 1599.9145 -299.6917) 
(list 1599.9155 -301.35) 
(list 1599.9163 -303.0083) 
(list 1599.9172 -304.6667) 
(list 1599.9181 -306.325) 
(list 1599.9189 -307.9833) 
(list 1599.9197 -309.6417) 
(list 1599.9204 -311.3) 
(list 1599.9212 -312.9583) 
(list 1599.9219 -314.6167) 
(list 1599.9226 -316.275) 
(list 1599.9233 -317.9333) 
(list 1599.9239 -319.5917) 
(list 1599.9245 -321.25) 
(list 1599.9251 -322.9083) 
(list 1599.9257 -324.5667) 
(list 1599.9262 -326.225) 
(list 1599.9268 -327.8833) 
(list 1599.9273 -329.5417) 
(list 1599.9278 -331.2) 
(list 1599.9283 -332.8583) 
(list 1599.9287 -334.5167) 
(list 1599.9291 -336.175) 
(list 1599.9296 -337.8333) 
(list 1599.93 -339.4917) 
(list 1599.9303 -341.15) 
(list 1599.9307 -342.8083) 
(list 1599.931 -344.4667) 
(list 1599.9314 -346.125) 
(list 1599.9317 -347.7833) 
(list 1599.932 -349.4417) 
(list 1599.9322 -351.1) 
(list 1599.9325 -352.7583) 
(list 1599.9328 -354.4167) 
(list 1599.933 -356.075) 
(list 1599.9332 -357.7333) 
(list 1599.9334 -359.3917) 
(list 1599.9336 -361.05) 
(list 1599.9338 -362.7083) 
(list 1599.934 -364.3667) 
(list 1599.9341 -366.025) 
(list 1599.9343 -367.6833) 
(list 1599.9344 -369.3417) 
(list 1599.9345 -371) 
(list 1599.9347 -372.6583) 
(list 1599.9348 -374.3167) 
(list 1599.9349 -375.975) 
(list 1599.9349 -377.6333) 
(list 1599.935 -379.2917) 
(list 1599.9351 -380.95) 
(list 1599.9352 -382.6083) 
(list 1599.9352 -384.2667) 
(list 1599.9353 -385.925) 
(list 1599.9353 -387.5833) 
(list 1599.9353 -389.2417) 
(list 1599.9354 -390.9) 
(list 1599.9354 -392.5583) 
(list 1599.9354 -394.2167) 
(list 1599.9354 -395.875) 
(list 1599.9355 -397.5333) 
(list 1599.9355 -399.1917) 
(list 1599.9355 -400.85) 
(list 1599.9355 -402.5083) 
(list 1599.9355 -404.1667) 
(list 1599.9355 -405.825) 
(list 1599.9355 -407.4833) 
(list 1599.9355 -409.1417) 
(list 1599.9355 -410.8)))
(apply 'command (append '("pline") coords '("c")))
(setq currobj (ssadd (entlast) currobj))
(command "_layer" "set" "prebias" "")
(command "_rectangle" "1599.815,-410.8" "1600.185,-211.8")
(setq currobj (ssadd (entlast) currobj))
(command "_layer" "set" "nitride" "")
(setq singlenanobeam5 currobj)
(setq currobj nil)
(setq currobj (ssadd))
; DRAWING NODE ARRAY
(setq coords (list 
(list 1600.185 -211.8) 
(list 1600.5625 -201.8) 
(list 1600.5625 -201.8) 
(list 1600.5625 -200.8) 
(list 1674.585 -212.6864) 
(list 1674.585 -207.7434) 
(list 1600.5625 -197.357) 
(list 1600.5625 -196.357) 
(list 1600.5625 -196.357) 
(list 1600.2625 -186.357) 
(list 1599.7375 -186.357) 
(list 1599.4375 -196.357) 
(list 1599.4375 -196.357) 
(list 1599.4375 -197.357) 
(list 1525.415 -207.7434) 
(list 1525.415 -212.6864) 
(list 1599.4375 -200.8) 
(list 1599.4375 -201.8) 
(list 1599.4375 -201.8) 
(list 1599.815 -211.8)))
(apply 'command (append '("pline") coords '("c")))
(setq currobj (ssadd (entlast) currobj))
(command "_layer" "set" "prebias" "")
(setq coords (list 
(list 1599.4375 -212.6864) 
(list 1599.4375 -200.8) 
(list 1525.415 -212.6864) 
(list 1525.415 -207.7434) 
(list 1599.4375 -197.357) 
(list 1599.4375 -186.357) 
(list 1600.5625 -186.357) 
(list 1600.5625 -197.357) 
(list 1674.585 -207.7434) 
(list 1674.585 -212.6864) 
(list 1600.5625 -200.8) 
(list 1600.5625 -212.6864)))
(apply 'command (append '("pline") coords '("c")))
(setq currobj (ssadd (entlast) currobj))
(command "_layer" "set" "nitride" "")
(command "_layer" "set" "fda1" "")
(setq coords (list 
(list 1600.5625 -200.657) 
(list 1674.585 -212.5434) 
(list 1674.585 -212.3664) 
(list 1600.5625 -200.58)))
(apply 'command (append '("pline") coords '("c")))
(setq currobj (ssadd (entlast) currobj))
(setq coords (list 
(list 1600.5625 -200.437) 
(list 1674.585 -212.2234) 
(list 1674.585 -212.0464) 
(list 1600.5625 -200.36)))
(apply 'command (append '("pline") coords '("c")))
(setq currobj (ssadd (entlast) currobj))
(setq coords (list 
(list 1600.5625 -200.217) 
(list 1674.585 -211.9034) 
(list 1674.585 -211.7264) 
(list 1600.5625 -200.14)))
(apply 'command (append '("pline") coords '("c")))
(setq currobj (ssadd (entlast) currobj))
(setq coords (list 
(list 1600.5625 -199.997) 
(list 1674.585 -211.5834) 
(list 1674.585 -211.4064) 
(list 1600.5625 -199.92)))
(apply 'command (append '("pline") coords '("c")))
(setq currobj (ssadd (entlast) currobj))
(setq coords (list 
(list 1600.5625 -199.777) 
(list 1674.585 -211.2634) 
(list 1674.585 -211.0864) 
(list 1600.5625 -199.7)))
(apply 'command (append '("pline") coords '("c")))
(setq currobj (ssadd (entlast) currobj))
(setq coords (list 
(list 1600.5625 -199.557) 
(list 1674.585 -210.9434) 
(list 1674.585 -210.7664) 
(list 1600.5625 -199.48)))
(apply 'command (append '("pline") coords '("c")))
(setq currobj (ssadd (entlast) currobj))
(setq coords (list 
(list 1600.5625 -199.337) 
(list 1674.585 -210.6234) 
(list 1674.585 -210.4464) 
(list 1600.5625 -199.26)))
(apply 'command (append '("pline") coords '("c")))
(setq currobj (ssadd (entlast) currobj))
(setq coords (list 
(list 1600.5625 -199.117) 
(list 1674.585 -210.3034) 
(list 1674.585 -210.1264) 
(list 1600.5625 -199.04)))
(apply 'command (append '("pline") coords '("c")))
(setq currobj (ssadd (entlast) currobj))
(setq coords (list 
(list 1600.5625 -198.897) 
(list 1674.585 -209.9834) 
(list 1674.585 -209.8064) 
(list 1600.5625 -198.82)))
(apply 'command (append '("pline") coords '("c")))
(setq currobj (ssadd (entlast) currobj))
(setq coords (list 
(list 1600.5625 -198.677) 
(list 1674.585 -209.6634) 
(list 1674.585 -209.4864) 
(list 1600.5625 -198.6)))
(apply 'command (append '("pline") coords '("c")))
(setq currobj (ssadd (entlast) currobj))
(setq coords (list 
(list 1600.5625 -198.457) 
(list 1674.585 -209.3434) 
(list 1674.585 -209.1664) 
(list 1600.5625 -198.38)))
(apply 'command (append '("pline") coords '("c")))
(setq currobj (ssadd (entlast) currobj))
(setq coords (list 
(list 1600.5625 -198.237) 
(list 1674.585 -209.0234) 
(list 1674.585 -208.8464) 
(list 1600.5625 -198.16)))
(apply 'command (append '("pline") coords '("c")))
(setq currobj (ssadd (entlast) currobj))
(setq coords (list 
(list 1600.5625 -198.017) 
(list 1674.585 -208.7034) 
(list 1674.585 -208.5264) 
(list 1600.5625 -197.94)))
(apply 'command (append '("pline") coords '("c")))
(setq currobj (ssadd (entlast) currobj))
(setq coords (list 
(list 1600.5625 -197.797) 
(list 1674.585 -208.3834) 
(list 1674.585 -208.2064) 
(list 1600.5625 -197.72)))
(apply 'command (append '("pline") coords '("c")))
(setq currobj (ssadd (entlast) currobj))
(setq coords (list 
(list 1600.5625 -197.577) 
(list 1674.585 -208.0634) 
(list 1674.585 -207.8864) 
(list 1600.5625 -197.5)))
(apply 'command (append '("pline") coords '("c")))
(setq currobj (ssadd (entlast) currobj))
(setq coords (list 
(list 1599.4375 -197.5) 
(list 1525.415 -207.8864) 
(list 1525.415 -208.0634) 
(list 1599.4375 -197.577)))
(apply 'command (append '("pline") coords '("c")))
(setq currobj (ssadd (entlast) currobj))
(setq coords (list 
(list 1599.4375 -197.72) 
(list 1525.415 -208.2064) 
(list 1525.415 -208.3834) 
(list 1599.4375 -197.797)))
(apply 'command (append '("pline") coords '("c")))
(setq currobj (ssadd (entlast) currobj))
(setq coords (list 
(list 1599.4375 -197.94) 
(list 1525.415 -208.5264) 
(list 1525.415 -208.7034) 
(list 1599.4375 -198.017)))
(apply 'command (append '("pline") coords '("c")))
(setq currobj (ssadd (entlast) currobj))
(setq coords (list 
(list 1599.4375 -198.16) 
(list 1525.415 -208.8464) 
(list 1525.415 -209.0234) 
(list 1599.4375 -198.237)))
(apply 'command (append '("pline") coords '("c")))
(setq currobj (ssadd (entlast) currobj))
(setq coords (list 
(list 1599.4375 -198.38) 
(list 1525.415 -209.1664) 
(list 1525.415 -209.3434) 
(list 1599.4375 -198.457)))
(apply 'command (append '("pline") coords '("c")))
(setq currobj (ssadd (entlast) currobj))
(setq coords (list 
(list 1599.4375 -198.6) 
(list 1525.415 -209.4864) 
(list 1525.415 -209.6634) 
(list 1599.4375 -198.677)))
(apply 'command (append '("pline") coords '("c")))
(setq currobj (ssadd (entlast) currobj))
(setq coords (list 
(list 1599.4375 -198.82) 
(list 1525.415 -209.8064) 
(list 1525.415 -209.9834) 
(list 1599.4375 -198.897)))
(apply 'command (append '("pline") coords '("c")))
(setq currobj (ssadd (entlast) currobj))
(setq coords (list 
(list 1599.4375 -199.04) 
(list 1525.415 -210.1264) 
(list 1525.415 -210.3034) 
(list 1599.4375 -199.117)))
(apply 'command (append '("pline") coords '("c")))
(setq currobj (ssadd (entlast) currobj))
(setq coords (list 
(list 1599.4375 -199.26) 
(list 1525.415 -210.4464) 
(list 1525.415 -210.6234) 
(list 1599.4375 -199.337)))
(apply 'command (append '("pline") coords '("c")))
(setq currobj (ssadd (entlast) currobj))
(setq coords (list 
(list 1599.4375 -199.48) 
(list 1525.415 -210.7664) 
(list 1525.415 -210.9434) 
(list 1599.4375 -199.557)))
(apply 'command (append '("pline") coords '("c")))
(setq currobj (ssadd (entlast) currobj))
(setq coords (list 
(list 1599.4375 -199.7) 
(list 1525.415 -211.0864) 
(list 1525.415 -211.2634) 
(list 1599.4375 -199.777)))
(apply 'command (append '("pline") coords '("c")))
(setq currobj (ssadd (entlast) currobj))
(setq coords (list 
(list 1599.4375 -199.92) 
(list 1525.415 -211.4064) 
(list 1525.415 -211.5834) 
(list 1599.4375 -199.997)))
(apply 'command (append '("pline") coords '("c")))
(setq currobj (ssadd (entlast) currobj))
(setq coords (list 
(list 1599.4375 -200.14) 
(list 1525.415 -211.7264) 
(list 1525.415 -211.9034) 
(list 1599.4375 -200.217)))
(apply 'command (append '("pline") coords '("c")))
(setq currobj (ssadd (entlast) currobj))
(setq coords (list 
(list 1599.4375 -200.36) 
(list 1525.415 -212.0464) 
(list 1525.415 -212.2234) 
(list 1599.4375 -200.437)))
(apply 'command (append '("pline") coords '("c")))
(setq currobj (ssadd (entlast) currobj))
(setq coords (list 
(list 1599.4375 -200.58) 
(list 1525.415 -212.3664) 
(list 1525.415 -212.5434) 
(list 1599.4375 -200.657)))
(apply 'command (append '("pline") coords '("c")))
(setq currobj (ssadd (entlast) currobj))
(command "_layer" "set" "nitride" "")
(command "_layer" "set" "text" "")
(command "_circle" "1598.985,-211.8" "0.075")
(command "_circle" "1598.985,-211.5" "0.075")
(command "_circle" "1598.985,-211.2" "0.075")
(command "_circle" "1598.985,-210.9" "0.075")
(command "_circle" "1598.985,-210.6" "0.075")
(command "_circle" "1598.685,-211.8" "0.075")
(command "_circle" "1598.685,-211.5" "0.075")
(command "_circle" "1598.685,-211.2" "0.075")
(command "_circle" "1598.685,-210.9" "0.075")
(command "_circle" "1598.685,-210.6" "0.075")
(command "_circle" "1598.385,-211.8" "0.075")
(command "_circle" "1598.385,-211.5" "0.075")
(command "_circle" "1598.385,-211.2" "0.075")
(command "_circle" "1598.385,-210.9" "0.075")
(command "_circle" "1598.385,-210.6" "0.075")
(command "_circle" "1598.085,-211.8" "0.075")
(command "_circle" "1598.085,-211.5" "0.075")
(command "_circle" "1598.085,-211.2" "0.075")
(command "_circle" "1598.085,-210.9" "0.075")
(command "_circle" "1598.085,-210.6" "0.075")
(command "_circle" "1597.785,-211.8" "0.075")
(command "_circle" "1597.785,-211.5" "0.075")
(command "_circle" "1597.785,-211.2" "0.075")
(command "_circle" "1597.785,-210.9" "0.075")
(command "_circle" "1597.785,-210.6" "0.075")
(command "_layer" "set" "nitride" "")
(setq anglednodearray5 currobj)
(setq currobj nil)
(setq currobj (ssadd))
; DRAWING COOLED SINGLE NANOBEAM
(setq coords (list 
(list 1600.2625 -186.357) 
(list 1600.2625 -181.357) 
(list 1599.7375 -181.357) 
(list 1599.7375 -186.357)))
(apply 'command (append '("pline") coords '("c")))
(setq currobj (ssadd (entlast) currobj))
(command "_layer" "set" "prebias" "")
(command "_rectangle" "1599.7375,-186.357" "1600.2625,-181.357")
(setq currobj (ssadd (entlast) currobj))
(command "_layer" "set" "nitride" "")
(setq coords (list 
(list 1600.2625 -181.357) 
(list 1600.5625 -171.357) 
(list 1600.5625 -171.357) 
(list 1600.5625 -170.357) 
(list 1674.585 -171.107) 
(list 1674.585 -166.164) 
(list 1600.5625 -166.914) 
(list 1600.5625 -165.914) 
(list 1600.5625 -165.914) 
(list 1600.2625 -155.914) 
(list 1599.7375 -155.914) 
(list 1599.4375 -165.914) 
(list 1599.4375 -165.914) 
(list 1599.4375 -166.914) 
(list 1525.415 -166.164) 
(list 1525.415 -171.107) 
(list 1599.4375 -170.357) 
(list 1599.4375 -171.357) 
(list 1599.4375 -171.357) 
(list 1599.7375 -181.357)))
(apply 'command (append '("pline") coords '("c")))
(setq currobj (ssadd (entlast) currobj))
(command "_layer" "set" "prebias" "")
(setq coords (list 
(list 1599.4375 -181.357) 
(list 1599.4375 -170.357) 
(list 1525.415 -171.107) 
(list 1525.415 -166.164) 
(list 1599.4375 -166.914) 
(list 1599.4375 -155.914) 
(list 1600.5625 -155.914) 
(list 1600.5625 -166.914) 
(list 1674.585 -166.164) 
(list 1674.585 -171.107) 
(list 1600.5625 -170.357) 
(list 1600.5625 -181.357)))
(apply 'command (append '("pline") coords '("c")))
(setq currobj (ssadd (entlast) currobj))
(command "_layer" "set" "nitride" "")
(command "_layer" "set" "fda1" "")
(setq coords (list 
(list 1600.5625 -170.214) 
(list 1674.585 -170.964) 
(list 1674.585 -170.787) 
(list 1600.5625 -170.137)))
(apply 'command (append '("pline") coords '("c")))
(setq currobj (ssadd (entlast) currobj))
(setq coords (list 
(list 1600.5625 -169.994) 
(list 1674.585 -170.644) 
(list 1674.585 -170.467) 
(list 1600.5625 -169.917)))
(apply 'command (append '("pline") coords '("c")))
(setq currobj (ssadd (entlast) currobj))
(setq coords (list 
(list 1600.5625 -169.774) 
(list 1674.585 -170.324) 
(list 1674.585 -170.147) 
(list 1600.5625 -169.697)))
(apply 'command (append '("pline") coords '("c")))
(setq currobj (ssadd (entlast) currobj))
(setq coords (list 
(list 1600.5625 -169.554) 
(list 1674.585 -170.004) 
(list 1674.585 -169.827) 
(list 1600.5625 -169.477)))
(apply 'command (append '("pline") coords '("c")))
(setq currobj (ssadd (entlast) currobj))
(setq coords (list 
(list 1600.5625 -169.334) 
(list 1674.585 -169.684) 
(list 1674.585 -169.507) 
(list 1600.5625 -169.257)))
(apply 'command (append '("pline") coords '("c")))
(setq currobj (ssadd (entlast) currobj))
(setq coords (list 
(list 1600.5625 -169.114) 
(list 1674.585 -169.364) 
(list 1674.585 -169.187) 
(list 1600.5625 -169.037)))
(apply 'command (append '("pline") coords '("c")))
(setq currobj (ssadd (entlast) currobj))
(setq coords (list 
(list 1600.5625 -168.894) 
(list 1674.585 -169.044) 
(list 1674.585 -168.867) 
(list 1600.5625 -168.817)))
(apply 'command (append '("pline") coords '("c")))
(setq currobj (ssadd (entlast) currobj))
(setq coords (list 
(list 1600.5625 -168.674) 
(list 1674.585 -168.724) 
(list 1674.585 -168.547) 
(list 1600.5625 -168.597)))
(apply 'command (append '("pline") coords '("c")))
(setq currobj (ssadd (entlast) currobj))
(setq coords (list 
(list 1600.5625 -168.454) 
(list 1674.585 -168.404) 
(list 1674.585 -168.227) 
(list 1600.5625 -168.377)))
(apply 'command (append '("pline") coords '("c")))
(setq currobj (ssadd (entlast) currobj))
(setq coords (list 
(list 1600.5625 -168.234) 
(list 1674.585 -168.084) 
(list 1674.585 -167.907) 
(list 1600.5625 -168.157)))
(apply 'command (append '("pline") coords '("c")))
(setq currobj (ssadd (entlast) currobj))
(setq coords (list 
(list 1600.5625 -168.014) 
(list 1674.585 -167.764) 
(list 1674.585 -167.587) 
(list 1600.5625 -167.937)))
(apply 'command (append '("pline") coords '("c")))
(setq currobj (ssadd (entlast) currobj))
(setq coords (list 
(list 1600.5625 -167.794) 
(list 1674.585 -167.444) 
(list 1674.585 -167.267) 
(list 1600.5625 -167.717)))
(apply 'command (append '("pline") coords '("c")))
(setq currobj (ssadd (entlast) currobj))
(setq coords (list 
(list 1600.5625 -167.574) 
(list 1674.585 -167.124) 
(list 1674.585 -166.947) 
(list 1600.5625 -167.497)))
(apply 'command (append '("pline") coords '("c")))
(setq currobj (ssadd (entlast) currobj))
(setq coords (list 
(list 1600.5625 -167.354) 
(list 1674.585 -166.804) 
(list 1674.585 -166.627) 
(list 1600.5625 -167.277)))
(apply 'command (append '("pline") coords '("c")))
(setq currobj (ssadd (entlast) currobj))
(setq coords (list 
(list 1600.5625 -167.134) 
(list 1674.585 -166.484) 
(list 1674.585 -166.307) 
(list 1600.5625 -167.057)))
(apply 'command (append '("pline") coords '("c")))
(setq currobj (ssadd (entlast) currobj))
(setq coords (list 
(list 1599.4375 -167.057) 
(list 1525.415 -166.307) 
(list 1525.415 -166.484) 
(list 1599.4375 -167.134)))
(apply 'command (append '("pline") coords '("c")))
(setq currobj (ssadd (entlast) currobj))
(setq coords (list 
(list 1599.4375 -167.277) 
(list 1525.415 -166.627) 
(list 1525.415 -166.804) 
(list 1599.4375 -167.354)))
(apply 'command (append '("pline") coords '("c")))
(setq currobj (ssadd (entlast) currobj))
(setq coords (list 
(list 1599.4375 -167.497) 
(list 1525.415 -166.947) 
(list 1525.415 -167.124) 
(list 1599.4375 -167.574)))
(apply 'command (append '("pline") coords '("c")))
(setq currobj (ssadd (entlast) currobj))
(setq coords (list 
(list 1599.4375 -167.717) 
(list 1525.415 -167.267) 
(list 1525.415 -167.444) 
(list 1599.4375 -167.794)))
(apply 'command (append '("pline") coords '("c")))
(setq currobj (ssadd (entlast) currobj))
(setq coords (list 
(list 1599.4375 -167.937) 
(list 1525.415 -167.587) 
(list 1525.415 -167.764) 
(list 1599.4375 -168.014)))
(apply 'command (append '("pline") coords '("c")))
(setq currobj (ssadd (entlast) currobj))
(setq coords (list 
(list 1599.4375 -168.157) 
(list 1525.415 -167.907) 
(list 1525.415 -168.084) 
(list 1599.4375 -168.234)))
(apply 'command (append '("pline") coords '("c")))
(setq currobj (ssadd (entlast) currobj))
(setq coords (list 
(list 1599.4375 -168.377) 
(list 1525.415 -168.227) 
(list 1525.415 -168.404) 
(list 1599.4375 -168.454)))
(apply 'command (append '("pline") coords '("c")))
(setq currobj (ssadd (entlast) currobj))
(setq coords (list 
(list 1599.4375 -168.597) 
(list 1525.415 -168.547) 
(list 1525.415 -168.724) 
(list 1599.4375 -168.674)))
(apply 'command (append '("pline") coords '("c")))
(setq currobj (ssadd (entlast) currobj))
(setq coords (list 
(list 1599.4375 -168.817) 
(list 1525.415 -168.867) 
(list 1525.415 -169.044) 
(list 1599.4375 -168.894)))
(apply 'command (append '("pline") coords '("c")))
(setq currobj (ssadd (entlast) currobj))
(setq coords (list 
(list 1599.4375 -169.037) 
(list 1525.415 -169.187) 
(list 1525.415 -169.364) 
(list 1599.4375 -169.114)))
(apply 'command (append '("pline") coords '("c")))
(setq currobj (ssadd (entlast) currobj))
(setq coords (list 
(list 1599.4375 -169.257) 
(list 1525.415 -169.507) 
(list 1525.415 -169.684) 
(list 1599.4375 -169.334)))
(apply 'command (append '("pline") coords '("c")))
(setq currobj (ssadd (entlast) currobj))
(setq coords (list 
(list 1599.4375 -169.477) 
(list 1525.415 -169.827) 
(list 1525.415 -170.004) 
(list 1599.4375 -169.554)))
(apply 'command (append '("pline") coords '("c")))
(setq currobj (ssadd (entlast) currobj))
(setq coords (list 
(list 1599.4375 -169.697) 
(list 1525.415 -170.147) 
(list 1525.415 -170.324) 
(list 1599.4375 -169.774)))
(apply 'command (append '("pline") coords '("c")))
(setq currobj (ssadd (entlast) currobj))
(setq coords (list 
(list 1599.4375 -169.917) 
(list 1525.415 -170.467) 
(list 1525.415 -170.644) 
(list 1599.4375 -169.994)))
(apply 'command (append '("pline") coords '("c")))
(setq currobj (ssadd (entlast) currobj))
(setq coords (list 
(list 1599.4375 -170.137) 
(list 1525.415 -170.787) 
(list 1525.415 -170.964) 
(list 1599.4375 -170.214)))
(apply 'command (append '("pline") coords '("c")))
(setq currobj (ssadd (entlast) currobj))
(command "_layer" "set" "nitride" "")
(command "_layer" "set" "text" "")
(command "_circle" "1599.0625,-181.357" "0.075")
(command "_circle" "1599.0625,-181.057" "0.075")
(command "_circle" "1599.0625,-180.757" "0.075")
(command "_circle" "1599.0625,-180.457" "0.075")
(command "_circle" "1599.0625,-180.157" "0.075")
(command "_circle" "1598.7625,-181.357" "0.075")
(command "_circle" "1598.7625,-181.057" "0.075")
(command "_circle" "1598.7625,-180.757" "0.075")
(command "_circle" "1598.7625,-180.457" "0.075")
(command "_circle" "1598.7625,-180.157" "0.075")
(command "_circle" "1598.4625,-181.357" "0.075")
(command "_circle" "1598.4625,-181.057" "0.075")
(command "_circle" "1598.4625,-180.757" "0.075")
(command "_circle" "1598.4625,-180.457" "0.075")
(command "_circle" "1598.4625,-180.157" "0.075")
(command "_circle" "1598.1625,-181.357" "0.075")
(command "_circle" "1598.1625,-181.057" "0.075")
(command "_circle" "1598.1625,-180.757" "0.075")
(command "_circle" "1598.1625,-180.457" "0.075")
(command "_circle" "1598.1625,-180.157" "0.075")
(command "_circle" "1597.8625,-181.357" "0.075")
(command "_circle" "1597.8625,-181.057" "0.075")
(command "_circle" "1597.8625,-180.757" "0.075")
(command "_circle" "1597.8625,-180.457" "0.075")
(command "_circle" "1597.8625,-180.157" "0.075")
(command "_layer" "set" "nitride" "")
(setq coords (list 
(list 1600.2625 -155.914) 
(list 1600.2625 -40.2693) 
(list 1599.7375 -40.2693) 
(list 1599.7375 -155.914)))
(apply 'command (append '("pline") coords '("c")))
(setq currobj (ssadd (entlast) currobj))
(command "_layer" "set" "prebias" "")
(command "_rectangle" "1599.7375,-155.914" "1600.2625,-40.2693")
(setq currobj (ssadd (entlast) currobj))
(command "_layer" "set" "nitride" "")
(setq coords (list 
(list 1600.2625 -40.2693) 
(list 1600.5625 -30.2693) 
(list 1600.5625 -30.2693) 
(list 1600.5625 -29.2693) 
(list 1674.585 -30.0193) 
(list 1674.585 -25.0763) 
(list 1600.5625 -25.8263) 
(list 1600.5625 -24.8263) 
(list 1600.5625 -24.8263) 
(list 1600.2625 -14.8263) 
(list 1599.7375 -14.8263) 
(list 1599.4375 -24.8263) 
(list 1599.4375 -24.8263) 
(list 1599.4375 -25.8263) 
(list 1525.415 -25.0763) 
(list 1525.415 -30.0193) 
(list 1599.4375 -29.2693) 
(list 1599.4375 -30.2693) 
(list 1599.4375 -30.2693) 
(list 1599.7375 -40.2693)))
(apply 'command (append '("pline") coords '("c")))
(setq currobj (ssadd (entlast) currobj))
(command "_layer" "set" "prebias" "")
(setq coords (list 
(list 1599.4375 -40.2693) 
(list 1599.4375 -29.2693) 
(list 1525.415 -30.0193) 
(list 1525.415 -25.0763) 
(list 1599.4375 -25.8263) 
(list 1599.4375 -14.8263) 
(list 1600.5625 -14.8263) 
(list 1600.5625 -25.8263) 
(list 1674.585 -25.0763) 
(list 1674.585 -30.0193) 
(list 1600.5625 -29.2693) 
(list 1600.5625 -40.2693)))
(apply 'command (append '("pline") coords '("c")))
(setq currobj (ssadd (entlast) currobj))
(command "_layer" "set" "nitride" "")
(command "_layer" "set" "fda1" "")
(setq coords (list 
(list 1600.5625 -29.1263) 
(list 1674.585 -29.8763) 
(list 1674.585 -29.6993) 
(list 1600.5625 -29.0493)))
(apply 'command (append '("pline") coords '("c")))
(setq currobj (ssadd (entlast) currobj))
(setq coords (list 
(list 1600.5625 -28.9063) 
(list 1674.585 -29.5563) 
(list 1674.585 -29.3793) 
(list 1600.5625 -28.8293)))
(apply 'command (append '("pline") coords '("c")))
(setq currobj (ssadd (entlast) currobj))
(setq coords (list 
(list 1600.5625 -28.6863) 
(list 1674.585 -29.2363) 
(list 1674.585 -29.0593) 
(list 1600.5625 -28.6093)))
(apply 'command (append '("pline") coords '("c")))
(setq currobj (ssadd (entlast) currobj))
(setq coords (list 
(list 1600.5625 -28.4663) 
(list 1674.585 -28.9163) 
(list 1674.585 -28.7393) 
(list 1600.5625 -28.3893)))
(apply 'command (append '("pline") coords '("c")))
(setq currobj (ssadd (entlast) currobj))
(setq coords (list 
(list 1600.5625 -28.2463) 
(list 1674.585 -28.5963) 
(list 1674.585 -28.4193) 
(list 1600.5625 -28.1693)))
(apply 'command (append '("pline") coords '("c")))
(setq currobj (ssadd (entlast) currobj))
(setq coords (list 
(list 1600.5625 -28.0263) 
(list 1674.585 -28.2763) 
(list 1674.585 -28.0993) 
(list 1600.5625 -27.9493)))
(apply 'command (append '("pline") coords '("c")))
(setq currobj (ssadd (entlast) currobj))
(setq coords (list 
(list 1600.5625 -27.8063) 
(list 1674.585 -27.9563) 
(list 1674.585 -27.7793) 
(list 1600.5625 -27.7293)))
(apply 'command (append '("pline") coords '("c")))
(setq currobj (ssadd (entlast) currobj))
(setq coords (list 
(list 1600.5625 -27.5863) 
(list 1674.585 -27.6363) 
(list 1674.585 -27.4593) 
(list 1600.5625 -27.5093)))
(apply 'command (append '("pline") coords '("c")))
(setq currobj (ssadd (entlast) currobj))
(setq coords (list 
(list 1600.5625 -27.3663) 
(list 1674.585 -27.3163) 
(list 1674.585 -27.1393) 
(list 1600.5625 -27.2893)))
(apply 'command (append '("pline") coords '("c")))
(setq currobj (ssadd (entlast) currobj))
(setq coords (list 
(list 1600.5625 -27.1463) 
(list 1674.585 -26.9963) 
(list 1674.585 -26.8193) 
(list 1600.5625 -27.0693)))
(apply 'command (append '("pline") coords '("c")))
(setq currobj (ssadd (entlast) currobj))
(setq coords (list 
(list 1600.5625 -26.9263) 
(list 1674.585 -26.6763) 
(list 1674.585 -26.4993) 
(list 1600.5625 -26.8493)))
(apply 'command (append '("pline") coords '("c")))
(setq currobj (ssadd (entlast) currobj))
(setq coords (list 
(list 1600.5625 -26.7063) 
(list 1674.585 -26.3563) 
(list 1674.585 -26.1793) 
(list 1600.5625 -26.6293)))
(apply 'command (append '("pline") coords '("c")))
(setq currobj (ssadd (entlast) currobj))
(setq coords (list 
(list 1600.5625 -26.4863) 
(list 1674.585 -26.0363) 
(list 1674.585 -25.8593) 
(list 1600.5625 -26.4093)))
(apply 'command (append '("pline") coords '("c")))
(setq currobj (ssadd (entlast) currobj))
(setq coords (list 
(list 1600.5625 -26.2663) 
(list 1674.585 -25.7163) 
(list 1674.585 -25.5393) 
(list 1600.5625 -26.1893)))
(apply 'command (append '("pline") coords '("c")))
(setq currobj (ssadd (entlast) currobj))
(setq coords (list 
(list 1600.5625 -26.0463) 
(list 1674.585 -25.3963) 
(list 1674.585 -25.2193) 
(list 1600.5625 -25.9693)))
(apply 'command (append '("pline") coords '("c")))
(setq currobj (ssadd (entlast) currobj))
(setq coords (list 
(list 1599.4375 -25.9693) 
(list 1525.415 -25.2193) 
(list 1525.415 -25.3963) 
(list 1599.4375 -26.0463)))
(apply 'command (append '("pline") coords '("c")))
(setq currobj (ssadd (entlast) currobj))
(setq coords (list 
(list 1599.4375 -26.1893) 
(list 1525.415 -25.5393) 
(list 1525.415 -25.7163) 
(list 1599.4375 -26.2663)))
(apply 'command (append '("pline") coords '("c")))
(setq currobj (ssadd (entlast) currobj))
(setq coords (list 
(list 1599.4375 -26.4093) 
(list 1525.415 -25.8593) 
(list 1525.415 -26.0363) 
(list 1599.4375 -26.4863)))
(apply 'command (append '("pline") coords '("c")))
(setq currobj (ssadd (entlast) currobj))
(setq coords (list 
(list 1599.4375 -26.6293) 
(list 1525.415 -26.1793) 
(list 1525.415 -26.3563) 
(list 1599.4375 -26.7063)))
(apply 'command (append '("pline") coords '("c")))
(setq currobj (ssadd (entlast) currobj))
(setq coords (list 
(list 1599.4375 -26.8493) 
(list 1525.415 -26.4993) 
(list 1525.415 -26.6763) 
(list 1599.4375 -26.9263)))
(apply 'command (append '("pline") coords '("c")))
(setq currobj (ssadd (entlast) currobj))
(setq coords (list 
(list 1599.4375 -27.0693) 
(list 1525.415 -26.8193) 
(list 1525.415 -26.9963) 
(list 1599.4375 -27.1463)))
(apply 'command (append '("pline") coords '("c")))
(setq currobj (ssadd (entlast) currobj))
(setq coords (list 
(list 1599.4375 -27.2893) 
(list 1525.415 -27.1393) 
(list 1525.415 -27.3163) 
(list 1599.4375 -27.3663)))
(apply 'command (append '("pline") coords '("c")))
(setq currobj (ssadd (entlast) currobj))
(setq coords (list 
(list 1599.4375 -27.5093) 
(list 1525.415 -27.4593) 
(list 1525.415 -27.6363) 
(list 1599.4375 -27.5863)))
(apply 'command (append '("pline") coords '("c")))
(setq currobj (ssadd (entlast) currobj))
(setq coords (list 
(list 1599.4375 -27.7293) 
(list 1525.415 -27.7793) 
(list 1525.415 -27.9563) 
(list 1599.4375 -27.8063)))
(apply 'command (append '("pline") coords '("c")))
(setq currobj (ssadd (entlast) currobj))
(setq coords (list 
(list 1599.4375 -27.9493) 
(list 1525.415 -28.0993) 
(list 1525.415 -28.2763) 
(list 1599.4375 -28.0263)))
(apply 'command (append '("pline") coords '("c")))
(setq currobj (ssadd (entlast) currobj))
(setq coords (list 
(list 1599.4375 -28.1693) 
(list 1525.415 -28.4193) 
(list 1525.415 -28.5963) 
(list 1599.4375 -28.2463)))
(apply 'command (append '("pline") coords '("c")))
(setq currobj (ssadd (entlast) currobj))
(setq coords (list 
(list 1599.4375 -28.3893) 
(list 1525.415 -28.7393) 
(list 1525.415 -28.9163) 
(list 1599.4375 -28.4663)))
(apply 'command (append '("pline") coords '("c")))
(setq currobj (ssadd (entlast) currobj))
(setq coords (list 
(list 1599.4375 -28.6093) 
(list 1525.415 -29.0593) 
(list 1525.415 -29.2363) 
(list 1599.4375 -28.6863)))
(apply 'command (append '("pline") coords '("c")))
(setq currobj (ssadd (entlast) currobj))
(setq coords (list 
(list 1599.4375 -28.8293) 
(list 1525.415 -29.3793) 
(list 1525.415 -29.5563) 
(list 1599.4375 -28.9063)))
(apply 'command (append '("pline") coords '("c")))
(setq currobj (ssadd (entlast) currobj))
(setq coords (list 
(list 1599.4375 -29.0493) 
(list 1525.415 -29.6993) 
(list 1525.415 -29.8763) 
(list 1599.4375 -29.1263)))
(apply 'command (append '("pline") coords '("c")))
(setq currobj (ssadd (entlast) currobj))
(command "_layer" "set" "nitride" "")
(command "_layer" "set" "text" "")
(command "_circle" "1599.0625,-40.2693" "0.075")
(command "_circle" "1599.0625,-39.9693" "0.075")
(command "_circle" "1599.0625,-39.6693" "0.075")
(command "_circle" "1599.0625,-39.3693" "0.075")
(command "_circle" "1599.0625,-39.0693" "0.075")
(command "_circle" "1598.7625,-40.2693" "0.075")
(command "_circle" "1598.7625,-39.9693" "0.075")
(command "_circle" "1598.7625,-39.6693" "0.075")
(command "_circle" "1598.7625,-39.3693" "0.075")
(command "_circle" "1598.7625,-39.0693" "0.075")
(command "_circle" "1598.4625,-40.2693" "0.075")
(command "_circle" "1598.4625,-39.9693" "0.075")
(command "_circle" "1598.4625,-39.6693" "0.075")
(command "_circle" "1598.4625,-39.3693" "0.075")
(command "_circle" "1598.4625,-39.0693" "0.075")
(command "_circle" "1598.1625,-40.2693" "0.075")
(command "_circle" "1598.1625,-39.9693" "0.075")
(command "_circle" "1598.1625,-39.6693" "0.075")
(command "_circle" "1598.1625,-39.3693" "0.075")
(command "_circle" "1598.1625,-39.0693" "0.075")
(command "_circle" "1597.8625,-40.2693" "0.075")
(command "_circle" "1597.8625,-39.9693" "0.075")
(command "_circle" "1597.8625,-39.6693" "0.075")
(command "_circle" "1597.8625,-39.3693" "0.075")
(command "_circle" "1597.8625,-39.0693" "0.075")
(command "_layer" "set" "nitride" "")
(setq coords (list 
(list 1600.2625 -14.8263) 
(list 1600.2625 100.8184) 
(list 1599.7375 100.8184) 
(list 1599.7375 -14.8263)))
(apply 'command (append '("pline") coords '("c")))
(setq currobj (ssadd (entlast) currobj))
(command "_layer" "set" "prebias" "")
(command "_rectangle" "1599.7375,-14.8263" "1600.2625,100.8184")
(setq currobj (ssadd (entlast) currobj))
(command "_layer" "set" "nitride" "")
(setq coords (list 
(list 1600.2625 100.8184) 
(list 1600.5625 110.8184) 
(list 1600.5625 110.8184) 
(list 1600.5625 111.8184) 
(list 1674.585 111.0684) 
(list 1674.585 116.0114) 
(list 1600.5625 115.2614) 
(list 1600.5625 116.2614) 
(list 1600.5625 116.2614) 
(list 1600.2625 126.2614) 
(list 1599.7375 126.2614) 
(list 1599.4375 116.2614) 
(list 1599.4375 116.2614) 
(list 1599.4375 115.2614) 
(list 1525.415 116.0114) 
(list 1525.415 111.0684) 
(list 1599.4375 111.8184) 
(list 1599.4375 110.8184) 
(list 1599.4375 110.8184) 
(list 1599.7375 100.8184)))
(apply 'command (append '("pline") coords '("c")))
(setq currobj (ssadd (entlast) currobj))
(command "_layer" "set" "prebias" "")
(setq coords (list 
(list 1599.4375 100.8184) 
(list 1599.4375 111.8184) 
(list 1525.415 111.0684) 
(list 1525.415 116.0114) 
(list 1599.4375 115.2614) 
(list 1599.4375 126.2614) 
(list 1600.5625 126.2614) 
(list 1600.5625 115.2614) 
(list 1674.585 116.0114) 
(list 1674.585 111.0684) 
(list 1600.5625 111.8184) 
(list 1600.5625 100.8184)))
(apply 'command (append '("pline") coords '("c")))
(setq currobj (ssadd (entlast) currobj))
(command "_layer" "set" "nitride" "")
(command "_layer" "set" "fda1" "")
(setq coords (list 
(list 1600.5625 111.9614) 
(list 1674.585 111.2114) 
(list 1674.585 111.3884) 
(list 1600.5625 112.0384)))
(apply 'command (append '("pline") coords '("c")))
(setq currobj (ssadd (entlast) currobj))
(setq coords (list 
(list 1600.5625 112.1814) 
(list 1674.585 111.5314) 
(list 1674.585 111.7084) 
(list 1600.5625 112.2584)))
(apply 'command (append '("pline") coords '("c")))
(setq currobj (ssadd (entlast) currobj))
(setq coords (list 
(list 1600.5625 112.4014) 
(list 1674.585 111.8514) 
(list 1674.585 112.0284) 
(list 1600.5625 112.4784)))
(apply 'command (append '("pline") coords '("c")))
(setq currobj (ssadd (entlast) currobj))
(setq coords (list 
(list 1600.5625 112.6214) 
(list 1674.585 112.1714) 
(list 1674.585 112.3484) 
(list 1600.5625 112.6984)))
(apply 'command (append '("pline") coords '("c")))
(setq currobj (ssadd (entlast) currobj))
(setq coords (list 
(list 1600.5625 112.8414) 
(list 1674.585 112.4914) 
(list 1674.585 112.6684) 
(list 1600.5625 112.9184)))
(apply 'command (append '("pline") coords '("c")))
(setq currobj (ssadd (entlast) currobj))
(setq coords (list 
(list 1600.5625 113.0614) 
(list 1674.585 112.8114) 
(list 1674.585 112.9884) 
(list 1600.5625 113.1384)))
(apply 'command (append '("pline") coords '("c")))
(setq currobj (ssadd (entlast) currobj))
(setq coords (list 
(list 1600.5625 113.2814) 
(list 1674.585 113.1314) 
(list 1674.585 113.3084) 
(list 1600.5625 113.3584)))
(apply 'command (append '("pline") coords '("c")))
(setq currobj (ssadd (entlast) currobj))
(setq coords (list 
(list 1600.5625 113.5014) 
(list 1674.585 113.4514) 
(list 1674.585 113.6284) 
(list 1600.5625 113.5784)))
(apply 'command (append '("pline") coords '("c")))
(setq currobj (ssadd (entlast) currobj))
(setq coords (list 
(list 1600.5625 113.7214) 
(list 1674.585 113.7714) 
(list 1674.585 113.9484) 
(list 1600.5625 113.7984)))
(apply 'command (append '("pline") coords '("c")))
(setq currobj (ssadd (entlast) currobj))
(setq coords (list 
(list 1600.5625 113.9414) 
(list 1674.585 114.0914) 
(list 1674.585 114.2684) 
(list 1600.5625 114.0184)))
(apply 'command (append '("pline") coords '("c")))
(setq currobj (ssadd (entlast) currobj))
(setq coords (list 
(list 1600.5625 114.1614) 
(list 1674.585 114.4114) 
(list 1674.585 114.5884) 
(list 1600.5625 114.2384)))
(apply 'command (append '("pline") coords '("c")))
(setq currobj (ssadd (entlast) currobj))
(setq coords (list 
(list 1600.5625 114.3814) 
(list 1674.585 114.7314) 
(list 1674.585 114.9084) 
(list 1600.5625 114.4584)))
(apply 'command (append '("pline") coords '("c")))
(setq currobj (ssadd (entlast) currobj))
(setq coords (list 
(list 1600.5625 114.6014) 
(list 1674.585 115.0514) 
(list 1674.585 115.2284) 
(list 1600.5625 114.6784)))
(apply 'command (append '("pline") coords '("c")))
(setq currobj (ssadd (entlast) currobj))
(setq coords (list 
(list 1600.5625 114.8214) 
(list 1674.585 115.3714) 
(list 1674.585 115.5484) 
(list 1600.5625 114.8984)))
(apply 'command (append '("pline") coords '("c")))
(setq currobj (ssadd (entlast) currobj))
(setq coords (list 
(list 1600.5625 115.0414) 
(list 1674.585 115.6914) 
(list 1674.585 115.8684) 
(list 1600.5625 115.1184)))
(apply 'command (append '("pline") coords '("c")))
(setq currobj (ssadd (entlast) currobj))
(setq coords (list 
(list 1599.4375 115.1184) 
(list 1525.415 115.8684) 
(list 1525.415 115.6914) 
(list 1599.4375 115.0414)))
(apply 'command (append '("pline") coords '("c")))
(setq currobj (ssadd (entlast) currobj))
(setq coords (list 
(list 1599.4375 114.8984) 
(list 1525.415 115.5484) 
(list 1525.415 115.3714) 
(list 1599.4375 114.8214)))
(apply 'command (append '("pline") coords '("c")))
(setq currobj (ssadd (entlast) currobj))
(setq coords (list 
(list 1599.4375 114.6784) 
(list 1525.415 115.2284) 
(list 1525.415 115.0514) 
(list 1599.4375 114.6014)))
(apply 'command (append '("pline") coords '("c")))
(setq currobj (ssadd (entlast) currobj))
(setq coords (list 
(list 1599.4375 114.4584) 
(list 1525.415 114.9084) 
(list 1525.415 114.7314) 
(list 1599.4375 114.3814)))
(apply 'command (append '("pline") coords '("c")))
(setq currobj (ssadd (entlast) currobj))
(setq coords (list 
(list 1599.4375 114.2384) 
(list 1525.415 114.5884) 
(list 1525.415 114.4114) 
(list 1599.4375 114.1614)))
(apply 'command (append '("pline") coords '("c")))
(setq currobj (ssadd (entlast) currobj))
(setq coords (list 
(list 1599.4375 114.0184) 
(list 1525.415 114.2684) 
(list 1525.415 114.0914) 
(list 1599.4375 113.9414)))
(apply 'command (append '("pline") coords '("c")))
(setq currobj (ssadd (entlast) currobj))
(setq coords (list 
(list 1599.4375 113.7984) 
(list 1525.415 113.9484) 
(list 1525.415 113.7714) 
(list 1599.4375 113.7214)))
(apply 'command (append '("pline") coords '("c")))
(setq currobj (ssadd (entlast) currobj))
(setq coords (list 
(list 1599.4375 113.5784) 
(list 1525.415 113.6284) 
(list 1525.415 113.4514) 
(list 1599.4375 113.5014)))
(apply 'command (append '("pline") coords '("c")))
(setq currobj (ssadd (entlast) currobj))
(setq coords (list 
(list 1599.4375 113.3584) 
(list 1525.415 113.3084) 
(list 1525.415 113.1314) 
(list 1599.4375 113.2814)))
(apply 'command (append '("pline") coords '("c")))
(setq currobj (ssadd (entlast) currobj))
(setq coords (list 
(list 1599.4375 113.1384) 
(list 1525.415 112.9884) 
(list 1525.415 112.8114) 
(list 1599.4375 113.0614)))
(apply 'command (append '("pline") coords '("c")))
(setq currobj (ssadd (entlast) currobj))
(setq coords (list 
(list 1599.4375 112.9184) 
(list 1525.415 112.6684) 
(list 1525.415 112.4914) 
(list 1599.4375 112.8414)))
(apply 'command (append '("pline") coords '("c")))
(setq currobj (ssadd (entlast) currobj))
(setq coords (list 
(list 1599.4375 112.6984) 
(list 1525.415 112.3484) 
(list 1525.415 112.1714) 
(list 1599.4375 112.6214)))
(apply 'command (append '("pline") coords '("c")))
(setq currobj (ssadd (entlast) currobj))
(setq coords (list 
(list 1599.4375 112.4784) 
(list 1525.415 112.0284) 
(list 1525.415 111.8514) 
(list 1599.4375 112.4014)))
(apply 'command (append '("pline") coords '("c")))
(setq currobj (ssadd (entlast) currobj))
(setq coords (list 
(list 1599.4375 112.2584) 
(list 1525.415 111.7084) 
(list 1525.415 111.5314) 
(list 1599.4375 112.1814)))
(apply 'command (append '("pline") coords '("c")))
(setq currobj (ssadd (entlast) currobj))
(setq coords (list 
(list 1599.4375 112.0384) 
(list 1525.415 111.3884) 
(list 1525.415 111.2114) 
(list 1599.4375 111.9614)))
(apply 'command (append '("pline") coords '("c")))
(setq currobj (ssadd (entlast) currobj))
(command "_layer" "set" "nitride" "")
(command "_layer" "set" "text" "")
(command "_circle" "1599.0625,100.8184" "0.075")
(command "_circle" "1599.0625,101.1184" "0.075")
(command "_circle" "1599.0625,101.4184" "0.075")
(command "_circle" "1599.0625,101.7184" "0.075")
(command "_circle" "1599.0625,102.0184" "0.075")
(command "_circle" "1598.7625,100.8184" "0.075")
(command "_circle" "1598.7625,101.1184" "0.075")
(command "_circle" "1598.7625,101.4184" "0.075")
(command "_circle" "1598.7625,101.7184" "0.075")
(command "_circle" "1598.7625,102.0184" "0.075")
(command "_circle" "1598.4625,100.8184" "0.075")
(command "_circle" "1598.4625,101.1184" "0.075")
(command "_circle" "1598.4625,101.4184" "0.075")
(command "_circle" "1598.4625,101.7184" "0.075")
(command "_circle" "1598.4625,102.0184" "0.075")
(command "_circle" "1598.1625,100.8184" "0.075")
(command "_circle" "1598.1625,101.1184" "0.075")
(command "_circle" "1598.1625,101.4184" "0.075")
(command "_circle" "1598.1625,101.7184" "0.075")
(command "_circle" "1598.1625,102.0184" "0.075")
(command "_circle" "1597.8625,100.8184" "0.075")
(command "_circle" "1597.8625,101.1184" "0.075")
(command "_circle" "1597.8625,101.4184" "0.075")
(command "_circle" "1597.8625,101.7184" "0.075")
(command "_circle" "1597.8625,102.0184" "0.075")
(command "_layer" "set" "nitride" "")
(setq coords (list 
(list 1600.2625 126.2614) 
(list 1600.2625 241.9061) 
(list 1599.7375 241.9061) 
(list 1599.7375 126.2614)))
(apply 'command (append '("pline") coords '("c")))
(setq currobj (ssadd (entlast) currobj))
(command "_layer" "set" "prebias" "")
(command "_rectangle" "1599.7375,126.2614" "1600.2625,241.9061")
(setq currobj (ssadd (entlast) currobj))
(command "_layer" "set" "nitride" "")
(setq coords (list 
(list 1600.2625 241.9061) 
(list 1600.5625 251.9061) 
(list 1600.5625 251.9061) 
(list 1600.5625 252.9061) 
(list 1674.585 252.1561) 
(list 1674.585 257.0991) 
(list 1600.5625 256.3491) 
(list 1600.5625 257.3491) 
(list 1600.5625 257.3491) 
(list 1600.2625 267.3491) 
(list 1599.7375 267.3491) 
(list 1599.4375 257.3491) 
(list 1599.4375 257.3491) 
(list 1599.4375 256.3491) 
(list 1525.415 257.0991) 
(list 1525.415 252.1561) 
(list 1599.4375 252.9061) 
(list 1599.4375 251.9061) 
(list 1599.4375 251.9061) 
(list 1599.7375 241.9061)))
(apply 'command (append '("pline") coords '("c")))
(setq currobj (ssadd (entlast) currobj))
(command "_layer" "set" "prebias" "")
(setq coords (list 
(list 1599.4375 241.9061) 
(list 1599.4375 252.9061) 
(list 1525.415 252.1561) 
(list 1525.415 257.0991) 
(list 1599.4375 256.3491) 
(list 1599.4375 267.3491) 
(list 1600.5625 267.3491) 
(list 1600.5625 256.3491) 
(list 1674.585 257.0991) 
(list 1674.585 252.1561) 
(list 1600.5625 252.9061) 
(list 1600.5625 241.9061)))
(apply 'command (append '("pline") coords '("c")))
(setq currobj (ssadd (entlast) currobj))
(command "_layer" "set" "nitride" "")
(command "_layer" "set" "fda1" "")
(setq coords (list 
(list 1600.5625 253.0491) 
(list 1674.585 252.2991) 
(list 1674.585 252.4761) 
(list 1600.5625 253.1261)))
(apply 'command (append '("pline") coords '("c")))
(setq currobj (ssadd (entlast) currobj))
(setq coords (list 
(list 1600.5625 253.2691) 
(list 1674.585 252.6191) 
(list 1674.585 252.7961) 
(list 1600.5625 253.3461)))
(apply 'command (append '("pline") coords '("c")))
(setq currobj (ssadd (entlast) currobj))
(setq coords (list 
(list 1600.5625 253.4891) 
(list 1674.585 252.9391) 
(list 1674.585 253.1161) 
(list 1600.5625 253.5661)))
(apply 'command (append '("pline") coords '("c")))
(setq currobj (ssadd (entlast) currobj))
(setq coords (list 
(list 1600.5625 253.7091) 
(list 1674.585 253.2591) 
(list 1674.585 253.4361) 
(list 1600.5625 253.7861)))
(apply 'command (append '("pline") coords '("c")))
(setq currobj (ssadd (entlast) currobj))
(setq coords (list 
(list 1600.5625 253.9291) 
(list 1674.585 253.5791) 
(list 1674.585 253.7561) 
(list 1600.5625 254.0061)))
(apply 'command (append '("pline") coords '("c")))
(setq currobj (ssadd (entlast) currobj))
(setq coords (list 
(list 1600.5625 254.1491) 
(list 1674.585 253.8991) 
(list 1674.585 254.0761) 
(list 1600.5625 254.2261)))
(apply 'command (append '("pline") coords '("c")))
(setq currobj (ssadd (entlast) currobj))
(setq coords (list 
(list 1600.5625 254.3691) 
(list 1674.585 254.2191) 
(list 1674.585 254.3961) 
(list 1600.5625 254.4461)))
(apply 'command (append '("pline") coords '("c")))
(setq currobj (ssadd (entlast) currobj))
(setq coords (list 
(list 1600.5625 254.5891) 
(list 1674.585 254.5391) 
(list 1674.585 254.7161) 
(list 1600.5625 254.6661)))
(apply 'command (append '("pline") coords '("c")))
(setq currobj (ssadd (entlast) currobj))
(setq coords (list 
(list 1600.5625 254.8091) 
(list 1674.585 254.8591) 
(list 1674.585 255.0361) 
(list 1600.5625 254.8861)))
(apply 'command (append '("pline") coords '("c")))
(setq currobj (ssadd (entlast) currobj))
(setq coords (list 
(list 1600.5625 255.0291) 
(list 1674.585 255.1791) 
(list 1674.585 255.3561) 
(list 1600.5625 255.1061)))
(apply 'command (append '("pline") coords '("c")))
(setq currobj (ssadd (entlast) currobj))
(setq coords (list 
(list 1600.5625 255.2491) 
(list 1674.585 255.4991) 
(list 1674.585 255.6761) 
(list 1600.5625 255.3261)))
(apply 'command (append '("pline") coords '("c")))
(setq currobj (ssadd (entlast) currobj))
(setq coords (list 
(list 1600.5625 255.4691) 
(list 1674.585 255.8191) 
(list 1674.585 255.9961) 
(list 1600.5625 255.5461)))
(apply 'command (append '("pline") coords '("c")))
(setq currobj (ssadd (entlast) currobj))
(setq coords (list 
(list 1600.5625 255.6891) 
(list 1674.585 256.1391) 
(list 1674.585 256.3161) 
(list 1600.5625 255.7661)))
(apply 'command (append '("pline") coords '("c")))
(setq currobj (ssadd (entlast) currobj))
(setq coords (list 
(list 1600.5625 255.9091) 
(list 1674.585 256.4591) 
(list 1674.585 256.6361) 
(list 1600.5625 255.9861)))
(apply 'command (append '("pline") coords '("c")))
(setq currobj (ssadd (entlast) currobj))
(setq coords (list 
(list 1600.5625 256.1291) 
(list 1674.585 256.7791) 
(list 1674.585 256.9561) 
(list 1600.5625 256.2061)))
(apply 'command (append '("pline") coords '("c")))
(setq currobj (ssadd (entlast) currobj))
(setq coords (list 
(list 1599.4375 256.2061) 
(list 1525.415 256.9561) 
(list 1525.415 256.7791) 
(list 1599.4375 256.1291)))
(apply 'command (append '("pline") coords '("c")))
(setq currobj (ssadd (entlast) currobj))
(setq coords (list 
(list 1599.4375 255.9861) 
(list 1525.415 256.6361) 
(list 1525.415 256.4591) 
(list 1599.4375 255.9091)))
(apply 'command (append '("pline") coords '("c")))
(setq currobj (ssadd (entlast) currobj))
(setq coords (list 
(list 1599.4375 255.7661) 
(list 1525.415 256.3161) 
(list 1525.415 256.1391) 
(list 1599.4375 255.6891)))
(apply 'command (append '("pline") coords '("c")))
(setq currobj (ssadd (entlast) currobj))
(setq coords (list 
(list 1599.4375 255.5461) 
(list 1525.415 255.9961) 
(list 1525.415 255.8191) 
(list 1599.4375 255.4691)))
(apply 'command (append '("pline") coords '("c")))
(setq currobj (ssadd (entlast) currobj))
(setq coords (list 
(list 1599.4375 255.3261) 
(list 1525.415 255.6761) 
(list 1525.415 255.4991) 
(list 1599.4375 255.2491)))
(apply 'command (append '("pline") coords '("c")))
(setq currobj (ssadd (entlast) currobj))
(setq coords (list 
(list 1599.4375 255.1061) 
(list 1525.415 255.3561) 
(list 1525.415 255.1791) 
(list 1599.4375 255.0291)))
(apply 'command (append '("pline") coords '("c")))
(setq currobj (ssadd (entlast) currobj))
(setq coords (list 
(list 1599.4375 254.8861) 
(list 1525.415 255.0361) 
(list 1525.415 254.8591) 
(list 1599.4375 254.8091)))
(apply 'command (append '("pline") coords '("c")))
(setq currobj (ssadd (entlast) currobj))
(setq coords (list 
(list 1599.4375 254.6661) 
(list 1525.415 254.7161) 
(list 1525.415 254.5391) 
(list 1599.4375 254.5891)))
(apply 'command (append '("pline") coords '("c")))
(setq currobj (ssadd (entlast) currobj))
(setq coords (list 
(list 1599.4375 254.4461) 
(list 1525.415 254.3961) 
(list 1525.415 254.2191) 
(list 1599.4375 254.3691)))
(apply 'command (append '("pline") coords '("c")))
(setq currobj (ssadd (entlast) currobj))
(setq coords (list 
(list 1599.4375 254.2261) 
(list 1525.415 254.0761) 
(list 1525.415 253.8991) 
(list 1599.4375 254.1491)))
(apply 'command (append '("pline") coords '("c")))
(setq currobj (ssadd (entlast) currobj))
(setq coords (list 
(list 1599.4375 254.0061) 
(list 1525.415 253.7561) 
(list 1525.415 253.5791) 
(list 1599.4375 253.9291)))
(apply 'command (append '("pline") coords '("c")))
(setq currobj (ssadd (entlast) currobj))
(setq coords (list 
(list 1599.4375 253.7861) 
(list 1525.415 253.4361) 
(list 1525.415 253.2591) 
(list 1599.4375 253.7091)))
(apply 'command (append '("pline") coords '("c")))
(setq currobj (ssadd (entlast) currobj))
(setq coords (list 
(list 1599.4375 253.5661) 
(list 1525.415 253.1161) 
(list 1525.415 252.9391) 
(list 1599.4375 253.4891)))
(apply 'command (append '("pline") coords '("c")))
(setq currobj (ssadd (entlast) currobj))
(setq coords (list 
(list 1599.4375 253.3461) 
(list 1525.415 252.7961) 
(list 1525.415 252.6191) 
(list 1599.4375 253.2691)))
(apply 'command (append '("pline") coords '("c")))
(setq currobj (ssadd (entlast) currobj))
(setq coords (list 
(list 1599.4375 253.1261) 
(list 1525.415 252.4761) 
(list 1525.415 252.2991) 
(list 1599.4375 253.0491)))
(apply 'command (append '("pline") coords '("c")))
(setq currobj (ssadd (entlast) currobj))
(command "_layer" "set" "nitride" "")
(command "_layer" "set" "text" "")
(command "_circle" "1599.0625,241.9061" "0.075")
(command "_circle" "1599.0625,242.2061" "0.075")
(command "_circle" "1599.0625,242.5061" "0.075")
(command "_circle" "1599.0625,242.8061" "0.075")
(command "_circle" "1599.0625,243.1061" "0.075")
(command "_circle" "1598.7625,241.9061" "0.075")
(command "_circle" "1598.7625,242.2061" "0.075")
(command "_circle" "1598.7625,242.5061" "0.075")
(command "_circle" "1598.7625,242.8061" "0.075")
(command "_circle" "1598.7625,243.1061" "0.075")
(command "_circle" "1598.4625,241.9061" "0.075")
(command "_circle" "1598.4625,242.2061" "0.075")
(command "_circle" "1598.4625,242.5061" "0.075")
(command "_circle" "1598.4625,242.8061" "0.075")
(command "_circle" "1598.4625,243.1061" "0.075")
(command "_circle" "1598.1625,241.9061" "0.075")
(command "_circle" "1598.1625,242.2061" "0.075")
(command "_circle" "1598.1625,242.5061" "0.075")
(command "_circle" "1598.1625,242.8061" "0.075")
(command "_circle" "1598.1625,243.1061" "0.075")
(command "_circle" "1597.8625,241.9061" "0.075")
(command "_circle" "1597.8625,242.2061" "0.075")
(command "_circle" "1597.8625,242.5061" "0.075")
(command "_circle" "1597.8625,242.8061" "0.075")
(command "_circle" "1597.8625,243.1061" "0.075")
(command "_layer" "set" "nitride" "")
(setq coords (list 
(list 1600.2625 267.3491) 
(list 1600.2625 382.9939) 
(list 1599.7375 382.9939) 
(list 1599.7375 267.3491)))
(apply 'command (append '("pline") coords '("c")))
(setq currobj (ssadd (entlast) currobj))
(command "_layer" "set" "prebias" "")
(command "_rectangle" "1599.7375,267.3491" "1600.2625,382.9939")
(setq currobj (ssadd (entlast) currobj))
(command "_layer" "set" "nitride" "")
(setq coords (list 
(list 1600.2625 382.9939) 
(list 1600.5625 392.9939) 
(list 1600.5625 392.9939) 
(list 1600.5625 393.9939) 
(list 1674.585 393.2439) 
(list 1674.585 398.1869) 
(list 1600.5625 397.4369) 
(list 1600.5625 398.4369) 
(list 1600.5625 398.4369) 
(list 1600.2625 408.4369) 
(list 1599.7375 408.4369) 
(list 1599.4375 398.4369) 
(list 1599.4375 398.4369) 
(list 1599.4375 397.4369) 
(list 1525.415 398.1869) 
(list 1525.415 393.2439) 
(list 1599.4375 393.9939) 
(list 1599.4375 392.9939) 
(list 1599.4375 392.9939) 
(list 1599.7375 382.9939)))
(apply 'command (append '("pline") coords '("c")))
(setq currobj (ssadd (entlast) currobj))
(command "_layer" "set" "prebias" "")
(setq coords (list 
(list 1599.4375 382.9939) 
(list 1599.4375 393.9939) 
(list 1525.415 393.2439) 
(list 1525.415 398.1869) 
(list 1599.4375 397.4369) 
(list 1599.4375 408.4369) 
(list 1600.5625 408.4369) 
(list 1600.5625 397.4369) 
(list 1674.585 398.1869) 
(list 1674.585 393.2439) 
(list 1600.5625 393.9939) 
(list 1600.5625 382.9939)))
(apply 'command (append '("pline") coords '("c")))
(setq currobj (ssadd (entlast) currobj))
(command "_layer" "set" "nitride" "")
(command "_layer" "set" "fda1" "")
(setq coords (list 
(list 1600.5625 394.1369) 
(list 1674.585 393.3869) 
(list 1674.585 393.5639) 
(list 1600.5625 394.2139)))
(apply 'command (append '("pline") coords '("c")))
(setq currobj (ssadd (entlast) currobj))
(setq coords (list 
(list 1600.5625 394.3569) 
(list 1674.585 393.7069) 
(list 1674.585 393.8839) 
(list 1600.5625 394.4339)))
(apply 'command (append '("pline") coords '("c")))
(setq currobj (ssadd (entlast) currobj))
(setq coords (list 
(list 1600.5625 394.5769) 
(list 1674.585 394.0269) 
(list 1674.585 394.2039) 
(list 1600.5625 394.6539)))
(apply 'command (append '("pline") coords '("c")))
(setq currobj (ssadd (entlast) currobj))
(setq coords (list 
(list 1600.5625 394.7969) 
(list 1674.585 394.3469) 
(list 1674.585 394.5239) 
(list 1600.5625 394.8739)))
(apply 'command (append '("pline") coords '("c")))
(setq currobj (ssadd (entlast) currobj))
(setq coords (list 
(list 1600.5625 395.0169) 
(list 1674.585 394.6669) 
(list 1674.585 394.8439) 
(list 1600.5625 395.0939)))
(apply 'command (append '("pline") coords '("c")))
(setq currobj (ssadd (entlast) currobj))
(setq coords (list 
(list 1600.5625 395.2369) 
(list 1674.585 394.9869) 
(list 1674.585 395.1639) 
(list 1600.5625 395.3139)))
(apply 'command (append '("pline") coords '("c")))
(setq currobj (ssadd (entlast) currobj))
(setq coords (list 
(list 1600.5625 395.4569) 
(list 1674.585 395.3069) 
(list 1674.585 395.4839) 
(list 1600.5625 395.5339)))
(apply 'command (append '("pline") coords '("c")))
(setq currobj (ssadd (entlast) currobj))
(setq coords (list 
(list 1600.5625 395.6769) 
(list 1674.585 395.6269) 
(list 1674.585 395.8039) 
(list 1600.5625 395.7539)))
(apply 'command (append '("pline") coords '("c")))
(setq currobj (ssadd (entlast) currobj))
(setq coords (list 
(list 1600.5625 395.8969) 
(list 1674.585 395.9469) 
(list 1674.585 396.1239) 
(list 1600.5625 395.9739)))
(apply 'command (append '("pline") coords '("c")))
(setq currobj (ssadd (entlast) currobj))
(setq coords (list 
(list 1600.5625 396.1169) 
(list 1674.585 396.2669) 
(list 1674.585 396.4439) 
(list 1600.5625 396.1939)))
(apply 'command (append '("pline") coords '("c")))
(setq currobj (ssadd (entlast) currobj))
(setq coords (list 
(list 1600.5625 396.3369) 
(list 1674.585 396.5869) 
(list 1674.585 396.7639) 
(list 1600.5625 396.4139)))
(apply 'command (append '("pline") coords '("c")))
(setq currobj (ssadd (entlast) currobj))
(setq coords (list 
(list 1600.5625 396.5569) 
(list 1674.585 396.9069) 
(list 1674.585 397.0839) 
(list 1600.5625 396.6339)))
(apply 'command (append '("pline") coords '("c")))
(setq currobj (ssadd (entlast) currobj))
(setq coords (list 
(list 1600.5625 396.7769) 
(list 1674.585 397.2269) 
(list 1674.585 397.4039) 
(list 1600.5625 396.8539)))
(apply 'command (append '("pline") coords '("c")))
(setq currobj (ssadd (entlast) currobj))
(setq coords (list 
(list 1600.5625 396.9969) 
(list 1674.585 397.5469) 
(list 1674.585 397.7239) 
(list 1600.5625 397.0739)))
(apply 'command (append '("pline") coords '("c")))
(setq currobj (ssadd (entlast) currobj))
(setq coords (list 
(list 1600.5625 397.2169) 
(list 1674.585 397.8669) 
(list 1674.585 398.0439) 
(list 1600.5625 397.2939)))
(apply 'command (append '("pline") coords '("c")))
(setq currobj (ssadd (entlast) currobj))
(setq coords (list 
(list 1599.4375 397.2939) 
(list 1525.415 398.0439) 
(list 1525.415 397.8669) 
(list 1599.4375 397.2169)))
(apply 'command (append '("pline") coords '("c")))
(setq currobj (ssadd (entlast) currobj))
(setq coords (list 
(list 1599.4375 397.0739) 
(list 1525.415 397.7239) 
(list 1525.415 397.5469) 
(list 1599.4375 396.9969)))
(apply 'command (append '("pline") coords '("c")))
(setq currobj (ssadd (entlast) currobj))
(setq coords (list 
(list 1599.4375 396.8539) 
(list 1525.415 397.4039) 
(list 1525.415 397.2269) 
(list 1599.4375 396.7769)))
(apply 'command (append '("pline") coords '("c")))
(setq currobj (ssadd (entlast) currobj))
(setq coords (list 
(list 1599.4375 396.6339) 
(list 1525.415 397.0839) 
(list 1525.415 396.9069) 
(list 1599.4375 396.5569)))
(apply 'command (append '("pline") coords '("c")))
(setq currobj (ssadd (entlast) currobj))
(setq coords (list 
(list 1599.4375 396.4139) 
(list 1525.415 396.7639) 
(list 1525.415 396.5869) 
(list 1599.4375 396.3369)))
(apply 'command (append '("pline") coords '("c")))
(setq currobj (ssadd (entlast) currobj))
(setq coords (list 
(list 1599.4375 396.1939) 
(list 1525.415 396.4439) 
(list 1525.415 396.2669) 
(list 1599.4375 396.1169)))
(apply 'command (append '("pline") coords '("c")))
(setq currobj (ssadd (entlast) currobj))
(setq coords (list 
(list 1599.4375 395.9739) 
(list 1525.415 396.1239) 
(list 1525.415 395.9469) 
(list 1599.4375 395.8969)))
(apply 'command (append '("pline") coords '("c")))
(setq currobj (ssadd (entlast) currobj))
(setq coords (list 
(list 1599.4375 395.7539) 
(list 1525.415 395.8039) 
(list 1525.415 395.6269) 
(list 1599.4375 395.6769)))
(apply 'command (append '("pline") coords '("c")))
(setq currobj (ssadd (entlast) currobj))
(setq coords (list 
(list 1599.4375 395.5339) 
(list 1525.415 395.4839) 
(list 1525.415 395.3069) 
(list 1599.4375 395.4569)))
(apply 'command (append '("pline") coords '("c")))
(setq currobj (ssadd (entlast) currobj))
(setq coords (list 
(list 1599.4375 395.3139) 
(list 1525.415 395.1639) 
(list 1525.415 394.9869) 
(list 1599.4375 395.2369)))
(apply 'command (append '("pline") coords '("c")))
(setq currobj (ssadd (entlast) currobj))
(setq coords (list 
(list 1599.4375 395.0939) 
(list 1525.415 394.8439) 
(list 1525.415 394.6669) 
(list 1599.4375 395.0169)))
(apply 'command (append '("pline") coords '("c")))
(setq currobj (ssadd (entlast) currobj))
(setq coords (list 
(list 1599.4375 394.8739) 
(list 1525.415 394.5239) 
(list 1525.415 394.3469) 
(list 1599.4375 394.7969)))
(apply 'command (append '("pline") coords '("c")))
(setq currobj (ssadd (entlast) currobj))
(setq coords (list 
(list 1599.4375 394.6539) 
(list 1525.415 394.2039) 
(list 1525.415 394.0269) 
(list 1599.4375 394.5769)))
(apply 'command (append '("pline") coords '("c")))
(setq currobj (ssadd (entlast) currobj))
(setq coords (list 
(list 1599.4375 394.4339) 
(list 1525.415 393.8839) 
(list 1525.415 393.7069) 
(list 1599.4375 394.3569)))
(apply 'command (append '("pline") coords '("c")))
(setq currobj (ssadd (entlast) currobj))
(setq coords (list 
(list 1599.4375 394.2139) 
(list 1525.415 393.5639) 
(list 1525.415 393.3869) 
(list 1599.4375 394.1369)))
(apply 'command (append '("pline") coords '("c")))
(setq currobj (ssadd (entlast) currobj))
(command "_layer" "set" "nitride" "")
(command "_layer" "set" "text" "")
(command "_circle" "1599.0625,382.9939" "0.075")
(command "_circle" "1599.0625,383.2939" "0.075")
(command "_circle" "1599.0625,383.5939" "0.075")
(command "_circle" "1599.0625,383.8939" "0.075")
(command "_circle" "1599.0625,384.1939" "0.075")
(command "_circle" "1598.7625,382.9939" "0.075")
(command "_circle" "1598.7625,383.2939" "0.075")
(command "_circle" "1598.7625,383.5939" "0.075")
(command "_circle" "1598.7625,383.8939" "0.075")
(command "_circle" "1598.7625,384.1939" "0.075")
(command "_circle" "1598.4625,382.9939" "0.075")
(command "_circle" "1598.4625,383.2939" "0.075")
(command "_circle" "1598.4625,383.5939" "0.075")
(command "_circle" "1598.4625,383.8939" "0.075")
(command "_circle" "1598.4625,384.1939" "0.075")
(command "_circle" "1598.1625,382.9939" "0.075")
(command "_circle" "1598.1625,383.2939" "0.075")
(command "_circle" "1598.1625,383.5939" "0.075")
(command "_circle" "1598.1625,383.8939" "0.075")
(command "_circle" "1598.1625,384.1939" "0.075")
(command "_circle" "1597.8625,382.9939" "0.075")
(command "_circle" "1597.8625,383.2939" "0.075")
(command "_circle" "1597.8625,383.5939" "0.075")
(command "_circle" "1597.8625,383.8939" "0.075")
(command "_circle" "1597.8625,384.1939" "0.075")
(command "_layer" "set" "nitride" "")
(setq coords (list 
(list 1600.2625 408.4369) 
(list 1600.2625 524.0816) 
(list 1599.7375 524.0816) 
(list 1599.7375 408.4369)))
(apply 'command (append '("pline") coords '("c")))
(setq currobj (ssadd (entlast) currobj))
(command "_layer" "set" "prebias" "")
(command "_rectangle" "1599.7375,408.4369" "1600.2625,524.0816")
(setq currobj (ssadd (entlast) currobj))
(command "_layer" "set" "nitride" "")
(setq coords (list 
(list 1600.2625 524.0816) 
(list 1600.5625 534.0816) 
(list 1600.5625 534.0816) 
(list 1600.5625 535.0816) 
(list 1674.585 534.3316) 
(list 1674.585 539.2746) 
(list 1600.5625 538.5246) 
(list 1600.5625 539.5246) 
(list 1600.5625 539.5246) 
(list 1600.2625 549.5246) 
(list 1599.7375 549.5246) 
(list 1599.4375 539.5246) 
(list 1599.4375 539.5246) 
(list 1599.4375 538.5246) 
(list 1525.415 539.2746) 
(list 1525.415 534.3316) 
(list 1599.4375 535.0816) 
(list 1599.4375 534.0816) 
(list 1599.4375 534.0816) 
(list 1599.7375 524.0816)))
(apply 'command (append '("pline") coords '("c")))
(setq currobj (ssadd (entlast) currobj))
(command "_layer" "set" "prebias" "")
(setq coords (list 
(list 1599.4375 524.0816) 
(list 1599.4375 535.0816) 
(list 1525.415 534.3316) 
(list 1525.415 539.2746) 
(list 1599.4375 538.5246) 
(list 1599.4375 549.5246) 
(list 1600.5625 549.5246) 
(list 1600.5625 538.5246) 
(list 1674.585 539.2746) 
(list 1674.585 534.3316) 
(list 1600.5625 535.0816) 
(list 1600.5625 524.0816)))
(apply 'command (append '("pline") coords '("c")))
(setq currobj (ssadd (entlast) currobj))
(command "_layer" "set" "nitride" "")
(command "_layer" "set" "fda1" "")
(setq coords (list 
(list 1600.5625 535.2246) 
(list 1674.585 534.4746) 
(list 1674.585 534.6516) 
(list 1600.5625 535.3016)))
(apply 'command (append '("pline") coords '("c")))
(setq currobj (ssadd (entlast) currobj))
(setq coords (list 
(list 1600.5625 535.4446) 
(list 1674.585 534.7946) 
(list 1674.585 534.9716) 
(list 1600.5625 535.5216)))
(apply 'command (append '("pline") coords '("c")))
(setq currobj (ssadd (entlast) currobj))
(setq coords (list 
(list 1600.5625 535.6646) 
(list 1674.585 535.1146) 
(list 1674.585 535.2916) 
(list 1600.5625 535.7416)))
(apply 'command (append '("pline") coords '("c")))
(setq currobj (ssadd (entlast) currobj))
(setq coords (list 
(list 1600.5625 535.8846) 
(list 1674.585 535.4346) 
(list 1674.585 535.6116) 
(list 1600.5625 535.9616)))
(apply 'command (append '("pline") coords '("c")))
(setq currobj (ssadd (entlast) currobj))
(setq coords (list 
(list 1600.5625 536.1046) 
(list 1674.585 535.7546) 
(list 1674.585 535.9316) 
(list 1600.5625 536.1816)))
(apply 'command (append '("pline") coords '("c")))
(setq currobj (ssadd (entlast) currobj))
(setq coords (list 
(list 1600.5625 536.3246) 
(list 1674.585 536.0746) 
(list 1674.585 536.2516) 
(list 1600.5625 536.4016)))
(apply 'command (append '("pline") coords '("c")))
(setq currobj (ssadd (entlast) currobj))
(setq coords (list 
(list 1600.5625 536.5446) 
(list 1674.585 536.3946) 
(list 1674.585 536.5716) 
(list 1600.5625 536.6216)))
(apply 'command (append '("pline") coords '("c")))
(setq currobj (ssadd (entlast) currobj))
(setq coords (list 
(list 1600.5625 536.7646) 
(list 1674.585 536.7146) 
(list 1674.585 536.8916) 
(list 1600.5625 536.8416)))
(apply 'command (append '("pline") coords '("c")))
(setq currobj (ssadd (entlast) currobj))
(setq coords (list 
(list 1600.5625 536.9846) 
(list 1674.585 537.0346) 
(list 1674.585 537.2116) 
(list 1600.5625 537.0616)))
(apply 'command (append '("pline") coords '("c")))
(setq currobj (ssadd (entlast) currobj))
(setq coords (list 
(list 1600.5625 537.2046) 
(list 1674.585 537.3546) 
(list 1674.585 537.5316) 
(list 1600.5625 537.2816)))
(apply 'command (append '("pline") coords '("c")))
(setq currobj (ssadd (entlast) currobj))
(setq coords (list 
(list 1600.5625 537.4246) 
(list 1674.585 537.6746) 
(list 1674.585 537.8516) 
(list 1600.5625 537.5016)))
(apply 'command (append '("pline") coords '("c")))
(setq currobj (ssadd (entlast) currobj))
(setq coords (list 
(list 1600.5625 537.6446) 
(list 1674.585 537.9946) 
(list 1674.585 538.1716) 
(list 1600.5625 537.7216)))
(apply 'command (append '("pline") coords '("c")))
(setq currobj (ssadd (entlast) currobj))
(setq coords (list 
(list 1600.5625 537.8646) 
(list 1674.585 538.3146) 
(list 1674.585 538.4916) 
(list 1600.5625 537.9416)))
(apply 'command (append '("pline") coords '("c")))
(setq currobj (ssadd (entlast) currobj))
(setq coords (list 
(list 1600.5625 538.0846) 
(list 1674.585 538.6346) 
(list 1674.585 538.8116) 
(list 1600.5625 538.1616)))
(apply 'command (append '("pline") coords '("c")))
(setq currobj (ssadd (entlast) currobj))
(setq coords (list 
(list 1600.5625 538.3046) 
(list 1674.585 538.9546) 
(list 1674.585 539.1316) 
(list 1600.5625 538.3816)))
(apply 'command (append '("pline") coords '("c")))
(setq currobj (ssadd (entlast) currobj))
(setq coords (list 
(list 1599.4375 538.3816) 
(list 1525.415 539.1316) 
(list 1525.415 538.9546) 
(list 1599.4375 538.3046)))
(apply 'command (append '("pline") coords '("c")))
(setq currobj (ssadd (entlast) currobj))
(setq coords (list 
(list 1599.4375 538.1616) 
(list 1525.415 538.8116) 
(list 1525.415 538.6346) 
(list 1599.4375 538.0846)))
(apply 'command (append '("pline") coords '("c")))
(setq currobj (ssadd (entlast) currobj))
(setq coords (list 
(list 1599.4375 537.9416) 
(list 1525.415 538.4916) 
(list 1525.415 538.3146) 
(list 1599.4375 537.8646)))
(apply 'command (append '("pline") coords '("c")))
(setq currobj (ssadd (entlast) currobj))
(setq coords (list 
(list 1599.4375 537.7216) 
(list 1525.415 538.1716) 
(list 1525.415 537.9946) 
(list 1599.4375 537.6446)))
(apply 'command (append '("pline") coords '("c")))
(setq currobj (ssadd (entlast) currobj))
(setq coords (list 
(list 1599.4375 537.5016) 
(list 1525.415 537.8516) 
(list 1525.415 537.6746) 
(list 1599.4375 537.4246)))
(apply 'command (append '("pline") coords '("c")))
(setq currobj (ssadd (entlast) currobj))
(setq coords (list 
(list 1599.4375 537.2816) 
(list 1525.415 537.5316) 
(list 1525.415 537.3546) 
(list 1599.4375 537.2046)))
(apply 'command (append '("pline") coords '("c")))
(setq currobj (ssadd (entlast) currobj))
(setq coords (list 
(list 1599.4375 537.0616) 
(list 1525.415 537.2116) 
(list 1525.415 537.0346) 
(list 1599.4375 536.9846)))
(apply 'command (append '("pline") coords '("c")))
(setq currobj (ssadd (entlast) currobj))
(setq coords (list 
(list 1599.4375 536.8416) 
(list 1525.415 536.8916) 
(list 1525.415 536.7146) 
(list 1599.4375 536.7646)))
(apply 'command (append '("pline") coords '("c")))
(setq currobj (ssadd (entlast) currobj))
(setq coords (list 
(list 1599.4375 536.6216) 
(list 1525.415 536.5716) 
(list 1525.415 536.3946) 
(list 1599.4375 536.5446)))
(apply 'command (append '("pline") coords '("c")))
(setq currobj (ssadd (entlast) currobj))
(setq coords (list 
(list 1599.4375 536.4016) 
(list 1525.415 536.2516) 
(list 1525.415 536.0746) 
(list 1599.4375 536.3246)))
(apply 'command (append '("pline") coords '("c")))
(setq currobj (ssadd (entlast) currobj))
(setq coords (list 
(list 1599.4375 536.1816) 
(list 1525.415 535.9316) 
(list 1525.415 535.7546) 
(list 1599.4375 536.1046)))
(apply 'command (append '("pline") coords '("c")))
(setq currobj (ssadd (entlast) currobj))
(setq coords (list 
(list 1599.4375 535.9616) 
(list 1525.415 535.6116) 
(list 1525.415 535.4346) 
(list 1599.4375 535.8846)))
(apply 'command (append '("pline") coords '("c")))
(setq currobj (ssadd (entlast) currobj))
(setq coords (list 
(list 1599.4375 535.7416) 
(list 1525.415 535.2916) 
(list 1525.415 535.1146) 
(list 1599.4375 535.6646)))
(apply 'command (append '("pline") coords '("c")))
(setq currobj (ssadd (entlast) currobj))
(setq coords (list 
(list 1599.4375 535.5216) 
(list 1525.415 534.9716) 
(list 1525.415 534.7946) 
(list 1599.4375 535.4446)))
(apply 'command (append '("pline") coords '("c")))
(setq currobj (ssadd (entlast) currobj))
(setq coords (list 
(list 1599.4375 535.3016) 
(list 1525.415 534.6516) 
(list 1525.415 534.4746) 
(list 1599.4375 535.2246)))
(apply 'command (append '("pline") coords '("c")))
(setq currobj (ssadd (entlast) currobj))
(command "_layer" "set" "nitride" "")
(command "_layer" "set" "text" "")
(command "_circle" "1599.0625,524.0816" "0.075")
(command "_circle" "1599.0625,524.3816" "0.075")
(command "_circle" "1599.0625,524.6816" "0.075")
(command "_circle" "1599.0625,524.9816" "0.075")
(command "_circle" "1599.0625,525.2816" "0.075")
(command "_circle" "1598.7625,524.0816" "0.075")
(command "_circle" "1598.7625,524.3816" "0.075")
(command "_circle" "1598.7625,524.6816" "0.075")
(command "_circle" "1598.7625,524.9816" "0.075")
(command "_circle" "1598.7625,525.2816" "0.075")
(command "_circle" "1598.4625,524.0816" "0.075")
(command "_circle" "1598.4625,524.3816" "0.075")
(command "_circle" "1598.4625,524.6816" "0.075")
(command "_circle" "1598.4625,524.9816" "0.075")
(command "_circle" "1598.4625,525.2816" "0.075")
(command "_circle" "1598.1625,524.0816" "0.075")
(command "_circle" "1598.1625,524.3816" "0.075")
(command "_circle" "1598.1625,524.6816" "0.075")
(command "_circle" "1598.1625,524.9816" "0.075")
(command "_circle" "1598.1625,525.2816" "0.075")
(command "_circle" "1597.8625,524.0816" "0.075")
(command "_circle" "1597.8625,524.3816" "0.075")
(command "_circle" "1597.8625,524.6816" "0.075")
(command "_circle" "1597.8625,524.9816" "0.075")
(command "_circle" "1597.8625,525.2816" "0.075")
(command "_layer" "set" "nitride" "")
(setq coords (list 
(list 1600.2625 549.5246) 
(list 1600.2625 665.1693) 
(list 1599.7375 665.1693) 
(list 1599.7375 549.5246)))
(apply 'command (append '("pline") coords '("c")))
(setq currobj (ssadd (entlast) currobj))
(command "_layer" "set" "prebias" "")
(command "_rectangle" "1599.7375,549.5246" "1600.2625,665.1693")
(setq currobj (ssadd (entlast) currobj))
(command "_layer" "set" "nitride" "")
(setq coords (list 
(list 1600.2625 665.1693) 
(list 1600.5625 675.1693) 
(list 1600.5625 675.1693) 
(list 1600.5625 676.1693) 
(list 1674.585 675.4193) 
(list 1674.585 680.3623) 
(list 1600.5625 679.6123) 
(list 1600.5625 680.6123) 
(list 1600.5625 680.6123) 
(list 1600.2625 690.6123) 
(list 1599.7375 690.6123) 
(list 1599.4375 680.6123) 
(list 1599.4375 680.6123) 
(list 1599.4375 679.6123) 
(list 1525.415 680.3623) 
(list 1525.415 675.4193) 
(list 1599.4375 676.1693) 
(list 1599.4375 675.1693) 
(list 1599.4375 675.1693) 
(list 1599.7375 665.1693)))
(apply 'command (append '("pline") coords '("c")))
(setq currobj (ssadd (entlast) currobj))
(command "_layer" "set" "prebias" "")
(setq coords (list 
(list 1599.4375 665.1693) 
(list 1599.4375 676.1693) 
(list 1525.415 675.4193) 
(list 1525.415 680.3623) 
(list 1599.4375 679.6123) 
(list 1599.4375 690.6123) 
(list 1600.5625 690.6123) 
(list 1600.5625 679.6123) 
(list 1674.585 680.3623) 
(list 1674.585 675.4193) 
(list 1600.5625 676.1693) 
(list 1600.5625 665.1693)))
(apply 'command (append '("pline") coords '("c")))
(setq currobj (ssadd (entlast) currobj))
(command "_layer" "set" "nitride" "")
(command "_layer" "set" "fda1" "")
(setq coords (list 
(list 1600.5625 676.3123) 
(list 1674.585 675.5623) 
(list 1674.585 675.7393) 
(list 1600.5625 676.3893)))
(apply 'command (append '("pline") coords '("c")))
(setq currobj (ssadd (entlast) currobj))
(setq coords (list 
(list 1600.5625 676.5323) 
(list 1674.585 675.8823) 
(list 1674.585 676.0593) 
(list 1600.5625 676.6093)))
(apply 'command (append '("pline") coords '("c")))
(setq currobj (ssadd (entlast) currobj))
(setq coords (list 
(list 1600.5625 676.7523) 
(list 1674.585 676.2023) 
(list 1674.585 676.3793) 
(list 1600.5625 676.8293)))
(apply 'command (append '("pline") coords '("c")))
(setq currobj (ssadd (entlast) currobj))
(setq coords (list 
(list 1600.5625 676.9723) 
(list 1674.585 676.5223) 
(list 1674.585 676.6993) 
(list 1600.5625 677.0493)))
(apply 'command (append '("pline") coords '("c")))
(setq currobj (ssadd (entlast) currobj))
(setq coords (list 
(list 1600.5625 677.1923) 
(list 1674.585 676.8423) 
(list 1674.585 677.0193) 
(list 1600.5625 677.2693)))
(apply 'command (append '("pline") coords '("c")))
(setq currobj (ssadd (entlast) currobj))
(setq coords (list 
(list 1600.5625 677.4123) 
(list 1674.585 677.1623) 
(list 1674.585 677.3393) 
(list 1600.5625 677.4893)))
(apply 'command (append '("pline") coords '("c")))
(setq currobj (ssadd (entlast) currobj))
(setq coords (list 
(list 1600.5625 677.6323) 
(list 1674.585 677.4823) 
(list 1674.585 677.6593) 
(list 1600.5625 677.7093)))
(apply 'command (append '("pline") coords '("c")))
(setq currobj (ssadd (entlast) currobj))
(setq coords (list 
(list 1600.5625 677.8523) 
(list 1674.585 677.8023) 
(list 1674.585 677.9793) 
(list 1600.5625 677.9293)))
(apply 'command (append '("pline") coords '("c")))
(setq currobj (ssadd (entlast) currobj))
(setq coords (list 
(list 1600.5625 678.0723) 
(list 1674.585 678.1223) 
(list 1674.585 678.2993) 
(list 1600.5625 678.1493)))
(apply 'command (append '("pline") coords '("c")))
(setq currobj (ssadd (entlast) currobj))
(setq coords (list 
(list 1600.5625 678.2923) 
(list 1674.585 678.4423) 
(list 1674.585 678.6193) 
(list 1600.5625 678.3693)))
(apply 'command (append '("pline") coords '("c")))
(setq currobj (ssadd (entlast) currobj))
(setq coords (list 
(list 1600.5625 678.5123) 
(list 1674.585 678.7623) 
(list 1674.585 678.9393) 
(list 1600.5625 678.5893)))
(apply 'command (append '("pline") coords '("c")))
(setq currobj (ssadd (entlast) currobj))
(setq coords (list 
(list 1600.5625 678.7323) 
(list 1674.585 679.0823) 
(list 1674.585 679.2593) 
(list 1600.5625 678.8093)))
(apply 'command (append '("pline") coords '("c")))
(setq currobj (ssadd (entlast) currobj))
(setq coords (list 
(list 1600.5625 678.9523) 
(list 1674.585 679.4023) 
(list 1674.585 679.5793) 
(list 1600.5625 679.0293)))
(apply 'command (append '("pline") coords '("c")))
(setq currobj (ssadd (entlast) currobj))
(setq coords (list 
(list 1600.5625 679.1723) 
(list 1674.585 679.7223) 
(list 1674.585 679.8993) 
(list 1600.5625 679.2493)))
(apply 'command (append '("pline") coords '("c")))
(setq currobj (ssadd (entlast) currobj))
(setq coords (list 
(list 1600.5625 679.3923) 
(list 1674.585 680.0423) 
(list 1674.585 680.2193) 
(list 1600.5625 679.4693)))
(apply 'command (append '("pline") coords '("c")))
(setq currobj (ssadd (entlast) currobj))
(setq coords (list 
(list 1599.4375 679.4693) 
(list 1525.415 680.2193) 
(list 1525.415 680.0423) 
(list 1599.4375 679.3923)))
(apply 'command (append '("pline") coords '("c")))
(setq currobj (ssadd (entlast) currobj))
(setq coords (list 
(list 1599.4375 679.2493) 
(list 1525.415 679.8993) 
(list 1525.415 679.7223) 
(list 1599.4375 679.1723)))
(apply 'command (append '("pline") coords '("c")))
(setq currobj (ssadd (entlast) currobj))
(setq coords (list 
(list 1599.4375 679.0293) 
(list 1525.415 679.5793) 
(list 1525.415 679.4023) 
(list 1599.4375 678.9523)))
(apply 'command (append '("pline") coords '("c")))
(setq currobj (ssadd (entlast) currobj))
(setq coords (list 
(list 1599.4375 678.8093) 
(list 1525.415 679.2593) 
(list 1525.415 679.0823) 
(list 1599.4375 678.7323)))
(apply 'command (append '("pline") coords '("c")))
(setq currobj (ssadd (entlast) currobj))
(setq coords (list 
(list 1599.4375 678.5893) 
(list 1525.415 678.9393) 
(list 1525.415 678.7623) 
(list 1599.4375 678.5123)))
(apply 'command (append '("pline") coords '("c")))
(setq currobj (ssadd (entlast) currobj))
(setq coords (list 
(list 1599.4375 678.3693) 
(list 1525.415 678.6193) 
(list 1525.415 678.4423) 
(list 1599.4375 678.2923)))
(apply 'command (append '("pline") coords '("c")))
(setq currobj (ssadd (entlast) currobj))
(setq coords (list 
(list 1599.4375 678.1493) 
(list 1525.415 678.2993) 
(list 1525.415 678.1223) 
(list 1599.4375 678.0723)))
(apply 'command (append '("pline") coords '("c")))
(setq currobj (ssadd (entlast) currobj))
(setq coords (list 
(list 1599.4375 677.9293) 
(list 1525.415 677.9793) 
(list 1525.415 677.8023) 
(list 1599.4375 677.8523)))
(apply 'command (append '("pline") coords '("c")))
(setq currobj (ssadd (entlast) currobj))
(setq coords (list 
(list 1599.4375 677.7093) 
(list 1525.415 677.6593) 
(list 1525.415 677.4823) 
(list 1599.4375 677.6323)))
(apply 'command (append '("pline") coords '("c")))
(setq currobj (ssadd (entlast) currobj))
(setq coords (list 
(list 1599.4375 677.4893) 
(list 1525.415 677.3393) 
(list 1525.415 677.1623) 
(list 1599.4375 677.4123)))
(apply 'command (append '("pline") coords '("c")))
(setq currobj (ssadd (entlast) currobj))
(setq coords (list 
(list 1599.4375 677.2693) 
(list 1525.415 677.0193) 
(list 1525.415 676.8423) 
(list 1599.4375 677.1923)))
(apply 'command (append '("pline") coords '("c")))
(setq currobj (ssadd (entlast) currobj))
(setq coords (list 
(list 1599.4375 677.0493) 
(list 1525.415 676.6993) 
(list 1525.415 676.5223) 
(list 1599.4375 676.9723)))
(apply 'command (append '("pline") coords '("c")))
(setq currobj (ssadd (entlast) currobj))
(setq coords (list 
(list 1599.4375 676.8293) 
(list 1525.415 676.3793) 
(list 1525.415 676.2023) 
(list 1599.4375 676.7523)))
(apply 'command (append '("pline") coords '("c")))
(setq currobj (ssadd (entlast) currobj))
(setq coords (list 
(list 1599.4375 676.6093) 
(list 1525.415 676.0593) 
(list 1525.415 675.8823) 
(list 1599.4375 676.5323)))
(apply 'command (append '("pline") coords '("c")))
(setq currobj (ssadd (entlast) currobj))
(setq coords (list 
(list 1599.4375 676.3893) 
(list 1525.415 675.7393) 
(list 1525.415 675.5623) 
(list 1599.4375 676.3123)))
(apply 'command (append '("pline") coords '("c")))
(setq currobj (ssadd (entlast) currobj))
(command "_layer" "set" "nitride" "")
(command "_layer" "set" "text" "")
(command "_circle" "1599.0625,665.1693" "0.075")
(command "_circle" "1599.0625,665.4693" "0.075")
(command "_circle" "1599.0625,665.7693" "0.075")
(command "_circle" "1599.0625,666.0693" "0.075")
(command "_circle" "1599.0625,666.3693" "0.075")
(command "_circle" "1598.7625,665.1693" "0.075")
(command "_circle" "1598.7625,665.4693" "0.075")
(command "_circle" "1598.7625,665.7693" "0.075")
(command "_circle" "1598.7625,666.0693" "0.075")
(command "_circle" "1598.7625,666.3693" "0.075")
(command "_circle" "1598.4625,665.1693" "0.075")
(command "_circle" "1598.4625,665.4693" "0.075")
(command "_circle" "1598.4625,665.7693" "0.075")
(command "_circle" "1598.4625,666.0693" "0.075")
(command "_circle" "1598.4625,666.3693" "0.075")
(command "_circle" "1598.1625,665.1693" "0.075")
(command "_circle" "1598.1625,665.4693" "0.075")
(command "_circle" "1598.1625,665.7693" "0.075")
(command "_circle" "1598.1625,666.0693" "0.075")
(command "_circle" "1598.1625,666.3693" "0.075")
(command "_circle" "1597.8625,665.1693" "0.075")
(command "_circle" "1597.8625,665.4693" "0.075")
(command "_circle" "1597.8625,665.7693" "0.075")
(command "_circle" "1597.8625,666.0693" "0.075")
(command "_circle" "1597.8625,666.3693" "0.075")
(command "_layer" "set" "nitride" "")
(setq coords (list 
(list 1600.2625 690.6123) 
(list 1600.2625 806.257) 
(list 1599.7375 806.257) 
(list 1599.7375 690.6123)))
(apply 'command (append '("pline") coords '("c")))
(setq currobj (ssadd (entlast) currobj))
(command "_layer" "set" "prebias" "")
(command "_rectangle" "1599.7375,690.6123" "1600.2625,806.257")
(setq currobj (ssadd (entlast) currobj))
(command "_layer" "set" "nitride" "")
(setq coords (list 
(list 1600.2625 806.257) 
(list 1600.5625 816.257) 
(list 1600.5625 816.257) 
(list 1600.5625 817.257) 
(list 1674.585 816.507) 
(list 1674.585 821.45) 
(list 1600.5625 820.7) 
(list 1600.5625 821.7) 
(list 1600.5625 821.7) 
(list 1600.2625 831.7) 
(list 1599.7375 831.7) 
(list 1599.4375 821.7) 
(list 1599.4375 821.7) 
(list 1599.4375 820.7) 
(list 1525.415 821.45) 
(list 1525.415 816.507) 
(list 1599.4375 817.257) 
(list 1599.4375 816.257) 
(list 1599.4375 816.257) 
(list 1599.7375 806.257)))
(apply 'command (append '("pline") coords '("c")))
(setq currobj (ssadd (entlast) currobj))
(command "_layer" "set" "prebias" "")
(setq coords (list 
(list 1599.4375 806.257) 
(list 1599.4375 817.257) 
(list 1525.415 816.507) 
(list 1525.415 821.45) 
(list 1599.4375 820.7) 
(list 1599.4375 831.7) 
(list 1600.5625 831.7) 
(list 1600.5625 820.7) 
(list 1674.585 821.45) 
(list 1674.585 816.507) 
(list 1600.5625 817.257) 
(list 1600.5625 806.257)))
(apply 'command (append '("pline") coords '("c")))
(setq currobj (ssadd (entlast) currobj))
(command "_layer" "set" "nitride" "")
(command "_layer" "set" "fda1" "")
(setq coords (list 
(list 1600.5625 817.4) 
(list 1674.585 816.65) 
(list 1674.585 816.827) 
(list 1600.5625 817.477)))
(apply 'command (append '("pline") coords '("c")))
(setq currobj (ssadd (entlast) currobj))
(setq coords (list 
(list 1600.5625 817.62) 
(list 1674.585 816.97) 
(list 1674.585 817.147) 
(list 1600.5625 817.697)))
(apply 'command (append '("pline") coords '("c")))
(setq currobj (ssadd (entlast) currobj))
(setq coords (list 
(list 1600.5625 817.84) 
(list 1674.585 817.29) 
(list 1674.585 817.467) 
(list 1600.5625 817.917)))
(apply 'command (append '("pline") coords '("c")))
(setq currobj (ssadd (entlast) currobj))
(setq coords (list 
(list 1600.5625 818.06) 
(list 1674.585 817.61) 
(list 1674.585 817.787) 
(list 1600.5625 818.137)))
(apply 'command (append '("pline") coords '("c")))
(setq currobj (ssadd (entlast) currobj))
(setq coords (list 
(list 1600.5625 818.28) 
(list 1674.585 817.93) 
(list 1674.585 818.107) 
(list 1600.5625 818.357)))
(apply 'command (append '("pline") coords '("c")))
(setq currobj (ssadd (entlast) currobj))
(setq coords (list 
(list 1600.5625 818.5) 
(list 1674.585 818.25) 
(list 1674.585 818.427) 
(list 1600.5625 818.577)))
(apply 'command (append '("pline") coords '("c")))
(setq currobj (ssadd (entlast) currobj))
(setq coords (list 
(list 1600.5625 818.72) 
(list 1674.585 818.57) 
(list 1674.585 818.747) 
(list 1600.5625 818.797)))
(apply 'command (append '("pline") coords '("c")))
(setq currobj (ssadd (entlast) currobj))
(setq coords (list 
(list 1600.5625 818.94) 
(list 1674.585 818.89) 
(list 1674.585 819.067) 
(list 1600.5625 819.017)))
(apply 'command (append '("pline") coords '("c")))
(setq currobj (ssadd (entlast) currobj))
(setq coords (list 
(list 1600.5625 819.16) 
(list 1674.585 819.21) 
(list 1674.585 819.387) 
(list 1600.5625 819.237)))
(apply 'command (append '("pline") coords '("c")))
(setq currobj (ssadd (entlast) currobj))
(setq coords (list 
(list 1600.5625 819.38) 
(list 1674.585 819.53) 
(list 1674.585 819.707) 
(list 1600.5625 819.457)))
(apply 'command (append '("pline") coords '("c")))
(setq currobj (ssadd (entlast) currobj))
(setq coords (list 
(list 1600.5625 819.6) 
(list 1674.585 819.85) 
(list 1674.585 820.027) 
(list 1600.5625 819.677)))
(apply 'command (append '("pline") coords '("c")))
(setq currobj (ssadd (entlast) currobj))
(setq coords (list 
(list 1600.5625 819.82) 
(list 1674.585 820.17) 
(list 1674.585 820.347) 
(list 1600.5625 819.897)))
(apply 'command (append '("pline") coords '("c")))
(setq currobj (ssadd (entlast) currobj))
(setq coords (list 
(list 1600.5625 820.04) 
(list 1674.585 820.49) 
(list 1674.585 820.667) 
(list 1600.5625 820.117)))
(apply 'command (append '("pline") coords '("c")))
(setq currobj (ssadd (entlast) currobj))
(setq coords (list 
(list 1600.5625 820.26) 
(list 1674.585 820.81) 
(list 1674.585 820.987) 
(list 1600.5625 820.337)))
(apply 'command (append '("pline") coords '("c")))
(setq currobj (ssadd (entlast) currobj))
(setq coords (list 
(list 1600.5625 820.48) 
(list 1674.585 821.13) 
(list 1674.585 821.307) 
(list 1600.5625 820.557)))
(apply 'command (append '("pline") coords '("c")))
(setq currobj (ssadd (entlast) currobj))
(setq coords (list 
(list 1599.4375 820.557) 
(list 1525.415 821.307) 
(list 1525.415 821.13) 
(list 1599.4375 820.48)))
(apply 'command (append '("pline") coords '("c")))
(setq currobj (ssadd (entlast) currobj))
(setq coords (list 
(list 1599.4375 820.337) 
(list 1525.415 820.987) 
(list 1525.415 820.81) 
(list 1599.4375 820.26)))
(apply 'command (append '("pline") coords '("c")))
(setq currobj (ssadd (entlast) currobj))
(setq coords (list 
(list 1599.4375 820.117) 
(list 1525.415 820.667) 
(list 1525.415 820.49) 
(list 1599.4375 820.04)))
(apply 'command (append '("pline") coords '("c")))
(setq currobj (ssadd (entlast) currobj))
(setq coords (list 
(list 1599.4375 819.897) 
(list 1525.415 820.347) 
(list 1525.415 820.17) 
(list 1599.4375 819.82)))
(apply 'command (append '("pline") coords '("c")))
(setq currobj (ssadd (entlast) currobj))
(setq coords (list 
(list 1599.4375 819.677) 
(list 1525.415 820.027) 
(list 1525.415 819.85) 
(list 1599.4375 819.6)))
(apply 'command (append '("pline") coords '("c")))
(setq currobj (ssadd (entlast) currobj))
(setq coords (list 
(list 1599.4375 819.457) 
(list 1525.415 819.707) 
(list 1525.415 819.53) 
(list 1599.4375 819.38)))
(apply 'command (append '("pline") coords '("c")))
(setq currobj (ssadd (entlast) currobj))
(setq coords (list 
(list 1599.4375 819.237) 
(list 1525.415 819.387) 
(list 1525.415 819.21) 
(list 1599.4375 819.16)))
(apply 'command (append '("pline") coords '("c")))
(setq currobj (ssadd (entlast) currobj))
(setq coords (list 
(list 1599.4375 819.017) 
(list 1525.415 819.067) 
(list 1525.415 818.89) 
(list 1599.4375 818.94)))
(apply 'command (append '("pline") coords '("c")))
(setq currobj (ssadd (entlast) currobj))
(setq coords (list 
(list 1599.4375 818.797) 
(list 1525.415 818.747) 
(list 1525.415 818.57) 
(list 1599.4375 818.72)))
(apply 'command (append '("pline") coords '("c")))
(setq currobj (ssadd (entlast) currobj))
(setq coords (list 
(list 1599.4375 818.577) 
(list 1525.415 818.427) 
(list 1525.415 818.25) 
(list 1599.4375 818.5)))
(apply 'command (append '("pline") coords '("c")))
(setq currobj (ssadd (entlast) currobj))
(setq coords (list 
(list 1599.4375 818.357) 
(list 1525.415 818.107) 
(list 1525.415 817.93) 
(list 1599.4375 818.28)))
(apply 'command (append '("pline") coords '("c")))
(setq currobj (ssadd (entlast) currobj))
(setq coords (list 
(list 1599.4375 818.137) 
(list 1525.415 817.787) 
(list 1525.415 817.61) 
(list 1599.4375 818.06)))
(apply 'command (append '("pline") coords '("c")))
(setq currobj (ssadd (entlast) currobj))
(setq coords (list 
(list 1599.4375 817.917) 
(list 1525.415 817.467) 
(list 1525.415 817.29) 
(list 1599.4375 817.84)))
(apply 'command (append '("pline") coords '("c")))
(setq currobj (ssadd (entlast) currobj))
(setq coords (list 
(list 1599.4375 817.697) 
(list 1525.415 817.147) 
(list 1525.415 816.97) 
(list 1599.4375 817.62)))
(apply 'command (append '("pline") coords '("c")))
(setq currobj (ssadd (entlast) currobj))
(setq coords (list 
(list 1599.4375 817.477) 
(list 1525.415 816.827) 
(list 1525.415 816.65) 
(list 1599.4375 817.4)))
(apply 'command (append '("pline") coords '("c")))
(setq currobj (ssadd (entlast) currobj))
(command "_layer" "set" "nitride" "")
(command "_layer" "set" "text" "")
(command "_circle" "1599.0625,806.257" "0.075")
(command "_circle" "1599.0625,806.557" "0.075")
(command "_circle" "1599.0625,806.857" "0.075")
(command "_circle" "1599.0625,807.157" "0.075")
(command "_circle" "1599.0625,807.457" "0.075")
(command "_circle" "1598.7625,806.257" "0.075")
(command "_circle" "1598.7625,806.557" "0.075")
(command "_circle" "1598.7625,806.857" "0.075")
(command "_circle" "1598.7625,807.157" "0.075")
(command "_circle" "1598.7625,807.457" "0.075")
(command "_circle" "1598.4625,806.257" "0.075")
(command "_circle" "1598.4625,806.557" "0.075")
(command "_circle" "1598.4625,806.857" "0.075")
(command "_circle" "1598.4625,807.157" "0.075")
(command "_circle" "1598.4625,807.457" "0.075")
(command "_circle" "1598.1625,806.257" "0.075")
(command "_circle" "1598.1625,806.557" "0.075")
(command "_circle" "1598.1625,806.857" "0.075")
(command "_circle" "1598.1625,807.157" "0.075")
(command "_circle" "1598.1625,807.457" "0.075")
(command "_circle" "1597.8625,806.257" "0.075")
(command "_circle" "1597.8625,806.557" "0.075")
(command "_circle" "1597.8625,806.857" "0.075")
(command "_circle" "1597.8625,807.157" "0.075")
(command "_circle" "1597.8625,807.457" "0.075")
(command "_layer" "set" "nitride" "")
(setq coords (list 
(list 1600.2625 831.7) 
(list 1600.2625 836.7) 
(list 1599.7375 836.7) 
(list 1599.7375 831.7)))
(apply 'command (append '("pline") coords '("c")))
(setq currobj (ssadd (entlast) currobj))
(command "_layer" "set" "prebias" "")
(command "_rectangle" "1599.7375,831.7" "1600.2625,836.7")
(setq currobj (ssadd (entlast) currobj))
(command "_layer" "set" "nitride" "")
(setq cooledsinglenanobeam5 currobj)
(setq currobj nil)
(setq currobj (ssadd))
; DRAWING PHOTONIC CRYSTAL
(command "_layer" "set" "negYjunc" "")
(setq coords (list 
(list 1600.135 866.7) 
(list 1600 851.7) 
(list 1600 866.7)))
(apply 'command (append '("pline") coords '("c")))
(setq currobj (ssadd (entlast) currobj))
(setq coords (list 
(list 1600.2625 836.7) 
(list 1600.415 866.7) 
(list 1601.126 866.7) 
(list 1601.126 836.7)))
(apply 'command (append '("pline") coords '("c")))
(setq currobj (ssadd (entlast) currobj))
(setq coords (list 
(list 1599.865 866.7) 
(list 1600 851.7) 
(list 1600 866.7)))
(apply 'command (append '("pline") coords '("c")))
(setq currobj (ssadd (entlast) currobj))
(setq coords (list 
(list 1599.7375 836.7) 
(list 1599.585 866.7) 
(list 1598.874 866.7) 
(list 1598.874 836.7)))
(apply 'command (append '("pline") coords '("c")))
(setq currobj (ssadd (entlast) currobj))
(command "_layer" "set" "nitride" "")
(setq yjunction5 currobj)
(setq currobj nil)
(setq currobj (ssadd))
(setq tap5 nil)
(setq tap5 (ssadd))
(command "_layer" "set" "phc" "")
(setq coords (list 
(list 1600 866.7) 
(list 1600.135 866.7) 
(list 1600.135 866.7103) 
(list 1600.135 866.7206) 
(list 1600.135 866.7308) 
(list 1600.135 866.7411) 
(list 1600.135 866.7514) 
(list 1600.135 866.7617) 
(list 1600.135 866.7719) 
(list 1600.135 866.7822) 
(list 1600.135 866.7925) 
(list 1600.135 866.8028) 
(list 1600.135 866.8131) 
(list 1600.135 866.8233) 
(list 1600.135 866.8336) 
(list 1600.135 866.8439) 
(list 1600.135 866.8542) 
(list 1600.135 866.8644) 
(list 1600.135 866.8747) 
(list 1600.135 866.885) 
(list 1600.135 866.8953) 
(list 1600.135 866.9056) 
(list 1600.135 866.9158) 
(list 1600.135 866.9261) 
(list 1600.135 866.9364) 
(list 1600.135 866.9467) 
(list 1600.135 866.9569) 
(list 1600.135 866.9672) 
(list 1600.135 866.9775) 
(list 1600.135 866.9878) 
(list 1600.135 866.9981) 
(list 1600.135 867.0083) 
(list 1600.135 867.0186) 
(list 1600.135 867.0289) 
(list 1600.135 867.0392) 
(list 1600.135 867.0494) 
(list 1600.135 867.0597) 
(list 1600.135 867.07) 
(list 1600 867.07)))
(apply 'command (append '("pline") coords '("c")))
(setq tap5 (ssadd (entlast) tap5))
(command "_mirror" (entlast) "" "1600,900" "1600,901" "No")
(setq tap5 (ssadd (entlast) tap5))
(setq coords (list 
(list 1600.4249 866.7) 
(list 1600.415 866.7) 
(list 1600.4153 866.7103) 
(list 1600.4155 866.7206) 
(list 1600.4157 866.7308) 
(list 1600.4159 866.7411) 
(list 1600.4159 866.7514) 
(list 1600.4159 866.7617) 
(list 1600.4158 866.7719) 
(list 1600.4156 866.7822) 
(list 1600.4152 866.7925) 
(list 1600.4148 866.8028) 
(list 1600.4144 866.8131) 
(list 1600.4138 866.8233) 
(list 1600.4133 866.8336) 
(list 1600.4127 866.8439) 
(list 1600.4122 866.8542) 
(list 1600.4117 866.8644) 
(list 1600.4113 866.8747) 
(list 1600.411 866.885) 
(list 1600.4108 866.8953) 
(list 1600.4109 866.9056) 
(list 1600.411 866.9158) 
(list 1600.4114 866.9261) 
(list 1600.4119 866.9364) 
(list 1600.4126 866.9467) 
(list 1600.4135 866.9569) 
(list 1600.4146 866.9672) 
(list 1600.4157 866.9775) 
(list 1600.4169 866.9878) 
(list 1600.4182 866.9981) 
(list 1600.4195 867.0083) 
(list 1600.4207 867.0186) 
(list 1600.4219 867.0289) 
(list 1600.4229 867.0392) 
(list 1600.4238 867.0494) 
(list 1600.4245 867.0597) 
(list 1600.4249 867.07) 
(list 1600.4249 867.07)))
(apply 'command (append '("pline") coords '("c")))
(setq tap5 (ssadd (entlast) tap5))
(command "_mirror" (entlast) "" "1600,900" "1600,901" "No")
(setq tap5 (ssadd (entlast) tap5))
(setq coords (list 
(list 1601.126 866.7) 
(list 1600.4249 866.7) 
(list 1600.4249 866.7103) 
(list 1600.4249 866.7206) 
(list 1600.4249 866.7308) 
(list 1600.4249 866.7411) 
(list 1600.4249 866.7514) 
(list 1600.4249 866.7617) 
(list 1600.4249 866.7719) 
(list 1600.4249 866.7822) 
(list 1600.4249 866.7925) 
(list 1600.4249 866.8028) 
(list 1600.4249 866.8131) 
(list 1600.4249 866.8233) 
(list 1600.4249 866.8336) 
(list 1600.4249 866.8439) 
(list 1600.4249 866.8542) 
(list 1600.4249 866.8644) 
(list 1600.4249 866.8747) 
(list 1600.4249 866.885) 
(list 1600.4249 866.8953) 
(list 1600.4249 866.9056) 
(list 1600.4249 866.9158) 
(list 1600.4249 866.9261) 
(list 1600.4249 866.9364) 
(list 1600.4249 866.9467) 
(list 1600.4249 866.9569) 
(list 1600.4249 866.9672) 
(list 1600.4249 866.9775) 
(list 1600.4249 866.9878) 
(list 1600.4249 866.9981) 
(list 1600.4249 867.0083) 
(list 1600.4249 867.0186) 
(list 1600.4249 867.0289) 
(list 1600.4249 867.0392) 
(list 1600.4249 867.0494) 
(list 1600.4249 867.0597) 
(list 1600.4249 867.07) 
(list 1601.126 867.07)))
(apply 'command (append '("pline") coords '("c")))
(setq tap5 (ssadd (entlast) tap5))
(command "_mirror" (entlast) "" "1600,900" "1600,901" "No")
(setq tap5 (ssadd (entlast) tap5))
(setq coords (list 
(list 1600 867.07) 
(list 1600.135 867.07) 
(list 1600.135 867.0803) 
(list 1600.135 867.0906) 
(list 1600.135 867.1008) 
(list 1600.135 867.1111) 
(list 1600.135 867.1214) 
(list 1600.135 867.1317) 
(list 1600.135 867.1419) 
(list 1600.135 867.1522) 
(list 1600.135 867.1625) 
(list 1600.135 867.1728) 
(list 1600.135 867.1831) 
(list 1600.135 867.1933) 
(list 1600.135 867.2036) 
(list 1600.135 867.2139) 
(list 1600.135 867.2242) 
(list 1600.135 867.2344) 
(list 1600.135 867.2447) 
(list 1600.135 867.255) 
(list 1600.135 867.2653) 
(list 1600.135 867.2756) 
(list 1600.135 867.2858) 
(list 1600.135 867.2961) 
(list 1600.135 867.3064) 
(list 1600.135 867.3167) 
(list 1600.135 867.3269) 
(list 1600.135 867.3372) 
(list 1600.135 867.3475) 
(list 1600.135 867.3578) 
(list 1600.135 867.3681) 
(list 1600.135 867.3783) 
(list 1600.135 867.3886) 
(list 1600.135 867.3989) 
(list 1600.135 867.4092) 
(list 1600.135 867.4194) 
(list 1600.135 867.4297) 
(list 1600.135 867.44) 
(list 1600 867.44)))
(apply 'command (append '("pline") coords '("c")))
(setq tap5 (ssadd (entlast) tap5))
(command "_mirror" (entlast) "" "1600,900" "1600,901" "No")
(setq tap5 (ssadd (entlast) tap5))
(setq coords (list 
(list 1600.4347 867.07) 
(list 1600.4249 867.07) 
(list 1600.425 867.0803) 
(list 1600.4248 867.0906) 
(list 1600.4244 867.1008) 
(list 1600.4236 867.1111) 
(list 1600.4226 867.1214) 
(list 1600.4213 867.1317) 
(list 1600.4198 867.1419) 
(list 1600.418 867.1522) 
(list 1600.4162 867.1625) 
(list 1600.4142 867.1728) 
(list 1600.4122 867.1831) 
(list 1600.4103 867.1933) 
(list 1600.4085 867.2036) 
(list 1600.4068 867.2139) 
(list 1600.4054 867.2242) 
(list 1600.4042 867.2344) 
(list 1600.4034 867.2447) 
(list 1600.403 867.255) 
(list 1600.403 867.2653) 
(list 1600.4034 867.2756) 
(list 1600.4042 867.2858) 
(list 1600.4055 867.2961) 
(list 1600.4071 867.3064) 
(list 1600.4091 867.3167) 
(list 1600.4114 867.3269) 
(list 1600.4139 867.3372) 
(list 1600.4166 867.3475) 
(list 1600.4194 867.3578) 
(list 1600.4222 867.3681) 
(list 1600.4249 867.3783) 
(list 1600.4274 867.3886) 
(list 1600.4297 867.3989) 
(list 1600.4316 867.4092) 
(list 1600.4331 867.4194) 
(list 1600.4342 867.4297) 
(list 1600.4347 867.44) 
(list 1600.4347 867.44)))
(apply 'command (append '("pline") coords '("c")))
(setq tap5 (ssadd (entlast) tap5))
(command "_mirror" (entlast) "" "1600,900" "1600,901" "No")
(setq tap5 (ssadd (entlast) tap5))
(setq coords (list 
(list 1601.126 867.07) 
(list 1600.4347 867.07) 
(list 1600.4347 867.0803) 
(list 1600.4347 867.0906) 
(list 1600.4347 867.1008) 
(list 1600.4347 867.1111) 
(list 1600.4347 867.1214) 
(list 1600.4347 867.1317) 
(list 1600.4347 867.1419) 
(list 1600.4347 867.1522) 
(list 1600.4347 867.1625) 
(list 1600.4347 867.1728) 
(list 1600.4347 867.1831) 
(list 1600.4347 867.1933) 
(list 1600.4347 867.2036) 
(list 1600.4347 867.2139) 
(list 1600.4347 867.2242) 
(list 1600.4347 867.2344) 
(list 1600.4347 867.2447) 
(list 1600.4347 867.255) 
(list 1600.4347 867.2653) 
(list 1600.4347 867.2756) 
(list 1600.4347 867.2858) 
(list 1600.4347 867.2961) 
(list 1600.4347 867.3064) 
(list 1600.4347 867.3167) 
(list 1600.4347 867.3269) 
(list 1600.4347 867.3372) 
(list 1600.4347 867.3475) 
(list 1600.4347 867.3578) 
(list 1600.4347 867.3681) 
(list 1600.4347 867.3783) 
(list 1600.4347 867.3886) 
(list 1600.4347 867.3989) 
(list 1600.4347 867.4092) 
(list 1600.4347 867.4194) 
(list 1600.4347 867.4297) 
(list 1600.4347 867.44) 
(list 1601.126 867.44)))
(apply 'command (append '("pline") coords '("c")))
(setq tap5 (ssadd (entlast) tap5))
(command "_mirror" (entlast) "" "1600,900" "1600,901" "No")
(setq tap5 (ssadd (entlast) tap5))
(setq coords (list 
(list 1600 867.44) 
(list 1600.135 867.44) 
(list 1600.135 867.4503) 
(list 1600.135 867.4606) 
(list 1600.135 867.4708) 
(list 1600.135 867.4811) 
(list 1600.135 867.4914) 
(list 1600.135 867.5017) 
(list 1600.135 867.5119) 
(list 1600.135 867.5222) 
(list 1600.135 867.5325) 
(list 1600.135 867.5428) 
(list 1600.135 867.5531) 
(list 1600.135 867.5633) 
(list 1600.135 867.5736) 
(list 1600.135 867.5839) 
(list 1600.135 867.5942) 
(list 1600.135 867.6044) 
(list 1600.135 867.6147) 
(list 1600.135 867.625) 
(list 1600.135 867.6353) 
(list 1600.135 867.6456) 
(list 1600.135 867.6558) 
(list 1600.135 867.6661) 
(list 1600.135 867.6764) 
(list 1600.135 867.6867) 
(list 1600.135 867.6969) 
(list 1600.135 867.7072) 
(list 1600.135 867.7175) 
(list 1600.135 867.7278) 
(list 1600.135 867.7381) 
(list 1600.135 867.7483) 
(list 1600.135 867.7586) 
(list 1600.135 867.7689) 
(list 1600.135 867.7792) 
(list 1600.135 867.7894) 
(list 1600.135 867.7997) 
(list 1600.135 867.81) 
(list 1600 867.81)))
(apply 'command (append '("pline") coords '("c")))
(setq tap5 (ssadd (entlast) tap5))
(command "_mirror" (entlast) "" "1600,900" "1600,901" "No")
(setq tap5 (ssadd (entlast) tap5))
(setq coords (list 
(list 1600.4446 867.44) 
(list 1600.4347 867.44) 
(list 1600.4347 867.4503) 
(list 1600.4342 867.4606) 
(list 1600.4331 867.4708) 
(list 1600.4314 867.4811) 
(list 1600.4293 867.4914) 
(list 1600.4267 867.5017) 
(list 1600.4238 867.5119) 
(list 1600.4205 867.5222) 
(list 1600.4171 867.5325) 
(list 1600.4136 867.5428) 
(list 1600.4101 867.5531) 
(list 1600.4068 867.5633) 
(list 1600.4036 867.5736) 
(list 1600.4009 867.5839) 
(list 1600.3986 867.5942) 
(list 1600.3968 867.6044) 
(list 1600.3956 867.6147) 
(list 1600.395 867.625) 
(list 1600.3951 867.6353) 
(list 1600.3959 867.6456) 
(list 1600.3974 867.6558) 
(list 1600.3996 867.6661) 
(list 1600.4023 867.6764) 
(list 1600.4056 867.6867) 
(list 1600.4093 867.6969) 
(list 1600.4133 867.7072) 
(list 1600.4176 867.7175) 
(list 1600.4219 867.7278) 
(list 1600.4262 867.7381) 
(list 1600.4303 867.7483) 
(list 1600.4341 867.7586) 
(list 1600.4375 867.7689) 
(list 1600.4403 867.7792) 
(list 1600.4425 867.7894) 
(list 1600.4439 867.7997) 
(list 1600.4446 867.81) 
(list 1600.4446 867.81)))
(apply 'command (append '("pline") coords '("c")))
(setq tap5 (ssadd (entlast) tap5))
(command "_mirror" (entlast) "" "1600,900" "1600,901" "No")
(setq tap5 (ssadd (entlast) tap5))
(setq coords (list 
(list 1601.126 867.44) 
(list 1600.4446 867.44) 
(list 1600.4446 867.4503) 
(list 1600.4446 867.4606) 
(list 1600.4446 867.4708) 
(list 1600.4446 867.4811) 
(list 1600.4446 867.4914) 
(list 1600.4446 867.5017) 
(list 1600.4446 867.5119) 
(list 1600.4446 867.5222) 
(list 1600.4446 867.5325) 
(list 1600.4446 867.5428) 
(list 1600.4446 867.5531) 
(list 1600.4446 867.5633) 
(list 1600.4446 867.5736) 
(list 1600.4446 867.5839) 
(list 1600.4446 867.5942) 
(list 1600.4446 867.6044) 
(list 1600.4446 867.6147) 
(list 1600.4446 867.625) 
(list 1600.4446 867.6353) 
(list 1600.4446 867.6456) 
(list 1600.4446 867.6558) 
(list 1600.4446 867.6661) 
(list 1600.4446 867.6764) 
(list 1600.4446 867.6867) 
(list 1600.4446 867.6969) 
(list 1600.4446 867.7072) 
(list 1600.4446 867.7175) 
(list 1600.4446 867.7278) 
(list 1600.4446 867.7381) 
(list 1600.4446 867.7483) 
(list 1600.4446 867.7586) 
(list 1600.4446 867.7689) 
(list 1600.4446 867.7792) 
(list 1600.4446 867.7894) 
(list 1600.4446 867.7997) 
(list 1600.4446 867.81) 
(list 1601.126 867.81)))
(apply 'command (append '("pline") coords '("c")))
(setq tap5 (ssadd (entlast) tap5))
(command "_mirror" (entlast) "" "1600,900" "1600,901" "No")
(setq tap5 (ssadd (entlast) tap5))
(setq coords (list 
(list 1600 867.81) 
(list 1600.135 867.81) 
(list 1600.135 867.8203) 
(list 1600.135 867.8306) 
(list 1600.135 867.8408) 
(list 1600.135 867.8511) 
(list 1600.135 867.8614) 
(list 1600.135 867.8717) 
(list 1600.135 867.8819) 
(list 1600.135 867.8922) 
(list 1600.135 867.9025) 
(list 1600.135 867.9128) 
(list 1600.135 867.9231) 
(list 1600.135 867.9333) 
(list 1600.135 867.9436) 
(list 1600.135 867.9539) 
(list 1600.135 867.9642) 
(list 1600.135 867.9744) 
(list 1600.135 867.9847) 
(list 1600.135 867.995) 
(list 1600.135 868.0053) 
(list 1600.135 868.0156) 
(list 1600.135 868.0258) 
(list 1600.135 868.0361) 
(list 1600.135 868.0464) 
(list 1600.135 868.0567) 
(list 1600.135 868.0669) 
(list 1600.135 868.0772) 
(list 1600.135 868.0875) 
(list 1600.135 868.0978) 
(list 1600.135 868.1081) 
(list 1600.135 868.1183) 
(list 1600.135 868.1286) 
(list 1600.135 868.1389) 
(list 1600.135 868.1492) 
(list 1600.135 868.1594) 
(list 1600.135 868.1697) 
(list 1600.135 868.18) 
(list 1600 868.18)))
(apply 'command (append '("pline") coords '("c")))
(setq tap5 (ssadd (entlast) tap5))
(command "_mirror" (entlast) "" "1600,900" "1600,901" "No")
(setq tap5 (ssadd (entlast) tap5))
(setq coords (list 
(list 1600.4545 867.81) 
(list 1600.4446 867.81) 
(list 1600.4445 867.8203) 
(list 1600.4435 867.8306) 
(list 1600.4417 867.8408) 
(list 1600.4392 867.8511) 
(list 1600.436 867.8614) 
(list 1600.4321 867.8717) 
(list 1600.4277 867.8819) 
(list 1600.423 867.8922) 
(list 1600.418 867.9025) 
(list 1600.413 867.9128) 
(list 1600.408 867.9231) 
(list 1600.4032 867.9333) 
(list 1600.3988 867.9436) 
(list 1600.395 867.9539) 
(list 1600.3918 867.9642) 
(list 1600.3893 867.9744) 
(list 1600.3877 867.9847) 
(list 1600.387 867.995) 
(list 1600.3873 868.0053) 
(list 1600.3885 868.0156) 
(list 1600.3906 868.0258) 
(list 1600.3937 868.0361) 
(list 1600.3975 868.0464) 
(list 1600.402 868.0567) 
(list 1600.4072 868.0669) 
(list 1600.4127 868.0772) 
(list 1600.4185 868.0875) 
(list 1600.4244 868.0978) 
(list 1600.4302 868.1081) 
(list 1600.4357 868.1183) 
(list 1600.4408 868.1286) 
(list 1600.4452 868.1389) 
(list 1600.449 868.1492) 
(list 1600.4518 868.1594) 
(list 1600.4537 868.1697) 
(list 1600.4545 868.18) 
(list 1600.4545 868.18)))
(apply 'command (append '("pline") coords '("c")))
(setq tap5 (ssadd (entlast) tap5))
(command "_mirror" (entlast) "" "1600,900" "1600,901" "No")
(setq tap5 (ssadd (entlast) tap5))
(setq coords (list 
(list 1601.126 867.81) 
(list 1600.4545 867.81) 
(list 1600.4545 867.8203) 
(list 1600.4545 867.8306) 
(list 1600.4545 867.8408) 
(list 1600.4545 867.8511) 
(list 1600.4545 867.8614) 
(list 1600.4545 867.8717) 
(list 1600.4545 867.8819) 
(list 1600.4545 867.8922) 
(list 1600.4545 867.9025) 
(list 1600.4545 867.9128) 
(list 1600.4545 867.9231) 
(list 1600.4545 867.9333) 
(list 1600.4545 867.9436) 
(list 1600.4545 867.9539) 
(list 1600.4545 867.9642) 
(list 1600.4545 867.9744) 
(list 1600.4545 867.9847) 
(list 1600.4545 867.995) 
(list 1600.4545 868.0053) 
(list 1600.4545 868.0156) 
(list 1600.4545 868.0258) 
(list 1600.4545 868.0361) 
(list 1600.4545 868.0464) 
(list 1600.4545 868.0567) 
(list 1600.4545 868.0669) 
(list 1600.4545 868.0772) 
(list 1600.4545 868.0875) 
(list 1600.4545 868.0978) 
(list 1600.4545 868.1081) 
(list 1600.4545 868.1183) 
(list 1600.4545 868.1286) 
(list 1600.4545 868.1389) 
(list 1600.4545 868.1492) 
(list 1600.4545 868.1594) 
(list 1600.4545 868.1697) 
(list 1600.4545 868.18) 
(list 1601.126 868.18)))
(apply 'command (append '("pline") coords '("c")))
(setq tap5 (ssadd (entlast) tap5))
(command "_mirror" (entlast) "" "1600,900" "1600,901" "No")
(setq tap5 (ssadd (entlast) tap5))
(setq coords (list 
(list 1600 868.18) 
(list 1600.135 868.18) 
(list 1600.135 868.1903) 
(list 1600.135 868.2006) 
(list 1600.135 868.2108) 
(list 1600.135 868.2211) 
(list 1600.135 868.2314) 
(list 1600.135 868.2417) 
(list 1600.135 868.2519) 
(list 1600.135 868.2622) 
(list 1600.135 868.2725) 
(list 1600.135 868.2828) 
(list 1600.135 868.2931) 
(list 1600.135 868.3033) 
(list 1600.135 868.3136) 
(list 1600.135 868.3239) 
(list 1600.135 868.3342) 
(list 1600.135 868.3444) 
(list 1600.135 868.3547) 
(list 1600.135 868.365) 
(list 1600.135 868.3753) 
(list 1600.135 868.3856) 
(list 1600.135 868.3958) 
(list 1600.135 868.4061) 
(list 1600.135 868.4164) 
(list 1600.135 868.4267) 
(list 1600.135 868.4369) 
(list 1600.135 868.4472) 
(list 1600.135 868.4575) 
(list 1600.135 868.4678) 
(list 1600.135 868.4781) 
(list 1600.135 868.4883) 
(list 1600.135 868.4986) 
(list 1600.135 868.5089) 
(list 1600.135 868.5192) 
(list 1600.135 868.5294) 
(list 1600.135 868.5397) 
(list 1600.135 868.55) 
(list 1600 868.55)))
(apply 'command (append '("pline") coords '("c")))
(setq tap5 (ssadd (entlast) tap5))
(command "_mirror" (entlast) "" "1600,900" "1600,901" "No")
(setq tap5 (ssadd (entlast) tap5))
(setq coords (list 
(list 1600.4643 868.18) 
(list 1600.4545 868.18) 
(list 1600.4542 868.1903) 
(list 1600.4528 868.2006) 
(list 1600.4504 868.2108) 
(list 1600.447 868.2211) 
(list 1600.4426 868.2314) 
(list 1600.4375 868.2417) 
(list 1600.4317 868.2519) 
(list 1600.4255 868.2622) 
(list 1600.419 868.2725) 
(list 1600.4124 868.2828) 
(list 1600.4059 868.2931) 
(list 1600.3997 868.3033) 
(list 1600.394 868.3136) 
(list 1600.3891 868.3239) 
(list 1600.385 868.3342) 
(list 1600.3818 868.3444) 
(list 1600.3798 868.3547) 
(list 1600.379 868.365) 
(list 1600.3794 868.3753) 
(list 1600.381 868.3856) 
(list 1600.3838 868.3958) 
(list 1600.3877 868.4061) 
(list 1600.3927 868.4164) 
(list 1600.3985 868.4267) 
(list 1600.405 868.4369) 
(list 1600.4121 868.4472) 
(list 1600.4194 868.4575) 
(list 1600.4269 868.4678) 
(list 1600.4342 868.4781) 
(list 1600.4411 868.4883) 
(list 1600.4475 868.4986) 
(list 1600.453 868.5089) 
(list 1600.4576 868.5192) 
(list 1600.4611 868.5294) 
(list 1600.4634 868.5397) 
(list 1600.4643 868.55) 
(list 1600.4643 868.55)))
(apply 'command (append '("pline") coords '("c")))
(setq tap5 (ssadd (entlast) tap5))
(command "_mirror" (entlast) "" "1600,900" "1600,901" "No")
(setq tap5 (ssadd (entlast) tap5))
(setq coords (list 
(list 1601.126 868.18) 
(list 1600.4643 868.18) 
(list 1600.4643 868.1903) 
(list 1600.4643 868.2006) 
(list 1600.4643 868.2108) 
(list 1600.4643 868.2211) 
(list 1600.4643 868.2314) 
(list 1600.4643 868.2417) 
(list 1600.4643 868.2519) 
(list 1600.4643 868.2622) 
(list 1600.4643 868.2725) 
(list 1600.4643 868.2828) 
(list 1600.4643 868.2931) 
(list 1600.4643 868.3033) 
(list 1600.4643 868.3136) 
(list 1600.4643 868.3239) 
(list 1600.4643 868.3342) 
(list 1600.4643 868.3444) 
(list 1600.4643 868.3547) 
(list 1600.4643 868.365) 
(list 1600.4643 868.3753) 
(list 1600.4643 868.3856) 
(list 1600.4643 868.3958) 
(list 1600.4643 868.4061) 
(list 1600.4643 868.4164) 
(list 1600.4643 868.4267) 
(list 1600.4643 868.4369) 
(list 1600.4643 868.4472) 
(list 1600.4643 868.4575) 
(list 1600.4643 868.4678) 
(list 1600.4643 868.4781) 
(list 1600.4643 868.4883) 
(list 1600.4643 868.4986) 
(list 1600.4643 868.5089) 
(list 1600.4643 868.5192) 
(list 1600.4643 868.5294) 
(list 1600.4643 868.5397) 
(list 1600.4643 868.55) 
(list 1601.126 868.55)))
(apply 'command (append '("pline") coords '("c")))
(setq tap5 (ssadd (entlast) tap5))
(command "_mirror" (entlast) "" "1600,900" "1600,901" "No")
(setq tap5 (ssadd (entlast) tap5))
(setq coords (list 
(list 1600 868.55) 
(list 1600.135 868.55) 
(list 1600.135 868.5603) 
(list 1600.135 868.5706) 
(list 1600.135 868.5808) 
(list 1600.135 868.5911) 
(list 1600.135 868.6014) 
(list 1600.135 868.6117) 
(list 1600.135 868.6219) 
(list 1600.135 868.6322) 
(list 1600.135 868.6425) 
(list 1600.135 868.6528) 
(list 1600.135 868.6631) 
(list 1600.135 868.6733) 
(list 1600.135 868.6836) 
(list 1600.135 868.6939) 
(list 1600.135 868.7042) 
(list 1600.135 868.7144) 
(list 1600.135 868.7247) 
(list 1600.135 868.735) 
(list 1600.135 868.7453) 
(list 1600.135 868.7556) 
(list 1600.135 868.7658) 
(list 1600.135 868.7761) 
(list 1600.135 868.7864) 
(list 1600.135 868.7967) 
(list 1600.135 868.8069) 
(list 1600.135 868.8172) 
(list 1600.135 868.8275) 
(list 1600.135 868.8378) 
(list 1600.135 868.8481) 
(list 1600.135 868.8583) 
(list 1600.135 868.8686) 
(list 1600.135 868.8789) 
(list 1600.135 868.8892) 
(list 1600.135 868.8994) 
(list 1600.135 868.9097) 
(list 1600.135 868.92) 
(list 1600 868.92)))
(apply 'command (append '("pline") coords '("c")))
(setq tap5 (ssadd (entlast) tap5))
(command "_mirror" (entlast) "" "1600,900" "1600,901" "No")
(setq tap5 (ssadd (entlast) tap5))
(setq coords (list 
(list 1600.4742 868.55) 
(list 1600.4643 868.55) 
(list 1600.4639 868.5603) 
(list 1600.4622 868.5706) 
(list 1600.4591 868.5808) 
(list 1600.4547 868.5911) 
(list 1600.4493 868.6014) 
(list 1600.4429 868.6117) 
(list 1600.4357 868.6219) 
(list 1600.428 868.6322) 
(list 1600.4199 868.6425) 
(list 1600.4117 868.6528) 
(list 1600.4037 868.6631) 
(list 1600.3962 868.6733) 
(list 1600.3892 868.6836) 
(list 1600.3832 868.6939) 
(list 1600.3782 868.7042) 
(list 1600.3744 868.7144) 
(list 1600.372 868.7247) 
(list 1600.371 868.735) 
(list 1600.3715 868.7453) 
(list 1600.3735 868.7556) 
(list 1600.377 868.7658) 
(list 1600.3818 868.7761) 
(list 1600.3879 868.7864) 
(list 1600.395 868.7967) 
(list 1600.4029 868.8069) 
(list 1600.4115 868.8172) 
(list 1600.4204 868.8275) 
(list 1600.4294 868.8378) 
(list 1600.4382 868.8481) 
(list 1600.4465 868.8583) 
(list 1600.4541 868.8686) 
(list 1600.4608 868.8789) 
(list 1600.4663 868.8892) 
(list 1600.4704 868.8994) 
(list 1600.4731 868.9097) 
(list 1600.4742 868.92) 
(list 1600.4742 868.92)))
(apply 'command (append '("pline") coords '("c")))
(setq tap5 (ssadd (entlast) tap5))
(command "_mirror" (entlast) "" "1600,900" "1600,901" "No")
(setq tap5 (ssadd (entlast) tap5))
(setq coords (list 
(list 1601.126 868.55) 
(list 1600.4742 868.55) 
(list 1600.4742 868.5603) 
(list 1600.4742 868.5706) 
(list 1600.4742 868.5808) 
(list 1600.4742 868.5911) 
(list 1600.4742 868.6014) 
(list 1600.4742 868.6117) 
(list 1600.4742 868.6219) 
(list 1600.4742 868.6322) 
(list 1600.4742 868.6425) 
(list 1600.4742 868.6528) 
(list 1600.4742 868.6631) 
(list 1600.4742 868.6733) 
(list 1600.4742 868.6836) 
(list 1600.4742 868.6939) 
(list 1600.4742 868.7042) 
(list 1600.4742 868.7144) 
(list 1600.4742 868.7247) 
(list 1600.4742 868.735) 
(list 1600.4742 868.7453) 
(list 1600.4742 868.7556) 
(list 1600.4742 868.7658) 
(list 1600.4742 868.7761) 
(list 1600.4742 868.7864) 
(list 1600.4742 868.7967) 
(list 1600.4742 868.8069) 
(list 1600.4742 868.8172) 
(list 1600.4742 868.8275) 
(list 1600.4742 868.8378) 
(list 1600.4742 868.8481) 
(list 1600.4742 868.8583) 
(list 1600.4742 868.8686) 
(list 1600.4742 868.8789) 
(list 1600.4742 868.8892) 
(list 1600.4742 868.8994) 
(list 1600.4742 868.9097) 
(list 1600.4742 868.92) 
(list 1601.126 868.92)))
(apply 'command (append '("pline") coords '("c")))
(setq tap5 (ssadd (entlast) tap5))
(command "_mirror" (entlast) "" "1600,900" "1600,901" "No")
(setq tap5 (ssadd (entlast) tap5))
(setq coords (list 
(list 1600 868.92) 
(list 1600.135 868.92) 
(list 1600.135 868.9303) 
(list 1600.135 868.9406) 
(list 1600.135 868.9508) 
(list 1600.135 868.9611) 
(list 1600.135 868.9714) 
(list 1600.135 868.9817) 
(list 1600.135 868.9919) 
(list 1600.135 869.0022) 
(list 1600.135 869.0125) 
(list 1600.135 869.0228) 
(list 1600.135 869.0331) 
(list 1600.135 869.0433) 
(list 1600.135 869.0536) 
(list 1600.135 869.0639) 
(list 1600.135 869.0742) 
(list 1600.135 869.0844) 
(list 1600.135 869.0947) 
(list 1600.135 869.105) 
(list 1600.135 869.1153) 
(list 1600.135 869.1256) 
(list 1600.135 869.1358) 
(list 1600.135 869.1461) 
(list 1600.135 869.1564) 
(list 1600.135 869.1667) 
(list 1600.135 869.1769) 
(list 1600.135 869.1872) 
(list 1600.135 869.1975) 
(list 1600.135 869.2078) 
(list 1600.135 869.2181) 
(list 1600.135 869.2283) 
(list 1600.135 869.2386) 
(list 1600.135 869.2489) 
(list 1600.135 869.2592) 
(list 1600.135 869.2694) 
(list 1600.135 869.2797) 
(list 1600.135 869.29) 
(list 1600 869.29)))
(apply 'command (append '("pline") coords '("c")))
(setq tap5 (ssadd (entlast) tap5))
(command "_mirror" (entlast) "" "1600,900" "1600,901" "No")
(setq tap5 (ssadd (entlast) tap5))
(setq coords (list 
(list 1600.4841 868.92) 
(list 1600.4742 868.92) 
(list 1600.4737 868.9303) 
(list 1600.4715 868.9406) 
(list 1600.4677 868.9508) 
(list 1600.4625 868.9611) 
(list 1600.456 868.9714) 
(list 1600.4483 868.9817) 
(list 1600.4397 868.9919) 
(list 1600.4305 869.0022) 
(list 1600.4208 869.0125) 
(list 1600.4111 869.0228) 
(list 1600.4016 869.0331) 
(list 1600.3926 869.0433) 
(list 1600.3844 869.0536) 
(list 1600.3772 869.0639) 
(list 1600.3713 869.0742) 
(list 1600.3669 869.0844) 
(list 1600.3641 869.0947) 
(list 1600.363 869.105) 
(list 1600.3637 869.1153) 
(list 1600.3661 869.1256) 
(list 1600.3702 869.1358) 
(list 1600.3759 869.1461) 
(list 1600.3831 869.1564) 
(list 1600.3914 869.1667) 
(list 1600.4008 869.1769) 
(list 1600.4108 869.1872) 
(list 1600.4213 869.1975) 
(list 1600.4318 869.2078) 
(list 1600.4421 869.2181) 
(list 1600.4519 869.2283) 
(list 1600.4608 869.2386) 
(list 1600.4686 869.2489) 
(list 1600.475 869.2592) 
(list 1600.4798 869.2694) 
(list 1600.4828 869.2797) 
(list 1600.4841 869.29) 
(list 1600.4841 869.29)))
(apply 'command (append '("pline") coords '("c")))
(setq tap5 (ssadd (entlast) tap5))
(command "_mirror" (entlast) "" "1600,900" "1600,901" "No")
(setq tap5 (ssadd (entlast) tap5))
(setq coords (list 
(list 1601.126 868.92) 
(list 1600.4841 868.92) 
(list 1600.4841 868.9303) 
(list 1600.4841 868.9406) 
(list 1600.4841 868.9508) 
(list 1600.4841 868.9611) 
(list 1600.4841 868.9714) 
(list 1600.4841 868.9817) 
(list 1600.4841 868.9919) 
(list 1600.4841 869.0022) 
(list 1600.4841 869.0125) 
(list 1600.4841 869.0228) 
(list 1600.4841 869.0331) 
(list 1600.4841 869.0433) 
(list 1600.4841 869.0536) 
(list 1600.4841 869.0639) 
(list 1600.4841 869.0742) 
(list 1600.4841 869.0844) 
(list 1600.4841 869.0947) 
(list 1600.4841 869.105) 
(list 1600.4841 869.1153) 
(list 1600.4841 869.1256) 
(list 1600.4841 869.1358) 
(list 1600.4841 869.1461) 
(list 1600.4841 869.1564) 
(list 1600.4841 869.1667) 
(list 1600.4841 869.1769) 
(list 1600.4841 869.1872) 
(list 1600.4841 869.1975) 
(list 1600.4841 869.2078) 
(list 1600.4841 869.2181) 
(list 1600.4841 869.2283) 
(list 1600.4841 869.2386) 
(list 1600.4841 869.2489) 
(list 1600.4841 869.2592) 
(list 1600.4841 869.2694) 
(list 1600.4841 869.2797) 
(list 1600.4841 869.29) 
(list 1601.126 869.29)))
(apply 'command (append '("pline") coords '("c")))
(setq tap5 (ssadd (entlast) tap5))
(command "_mirror" (entlast) "" "1600,900" "1600,901" "No")
(setq tap5 (ssadd (entlast) tap5))
(setq coords (list 
(list 1600 869.29) 
(list 1600.135 869.29) 
(list 1600.135 869.3003) 
(list 1600.135 869.3106) 
(list 1600.135 869.3208) 
(list 1600.135 869.3311) 
(list 1600.135 869.3414) 
(list 1600.135 869.3517) 
(list 1600.135 869.3619) 
(list 1600.135 869.3722) 
(list 1600.135 869.3825) 
(list 1600.135 869.3928) 
(list 1600.135 869.4031) 
(list 1600.135 869.4133) 
(list 1600.135 869.4236) 
(list 1600.135 869.4339) 
(list 1600.135 869.4442) 
(list 1600.135 869.4544) 
(list 1600.135 869.4647) 
(list 1600.135 869.475) 
(list 1600.135 869.4853) 
(list 1600.135 869.4956) 
(list 1600.135 869.5058) 
(list 1600.135 869.5161) 
(list 1600.135 869.5264) 
(list 1600.135 869.5367) 
(list 1600.135 869.5469) 
(list 1600.135 869.5572) 
(list 1600.135 869.5675) 
(list 1600.135 869.5778) 
(list 1600.135 869.5881) 
(list 1600.135 869.5983) 
(list 1600.135 869.6086) 
(list 1600.135 869.6189) 
(list 1600.135 869.6292) 
(list 1600.135 869.6394) 
(list 1600.135 869.6497) 
(list 1600.135 869.66) 
(list 1600 869.66)))
(apply 'command (append '("pline") coords '("c")))
(setq tap5 (ssadd (entlast) tap5))
(command "_mirror" (entlast) "" "1600,900" "1600,901" "No")
(setq tap5 (ssadd (entlast) tap5))
(setq coords (list 
(list 1600.4939 869.29) 
(list 1600.4841 869.29) 
(list 1600.4834 869.3003) 
(list 1600.4808 869.3106) 
(list 1600.4764 869.3208) 
(list 1600.4703 869.3311) 
(list 1600.4627 869.3414) 
(list 1600.4537 869.3517) 
(list 1600.4437 869.3619) 
(list 1600.4329 869.3722) 
(list 1600.4218 869.3825) 
(list 1600.4105 869.3928) 
(list 1600.3995 869.4031) 
(list 1600.3891 869.4133) 
(list 1600.3796 869.4236) 
(list 1600.3713 869.4339) 
(list 1600.3645 869.4442) 
(list 1600.3595 869.4544) 
(list 1600.3562 869.4647) 
(list 1600.355 869.475) 
(list 1600.3558 869.4853) 
(list 1600.3586 869.4956) 
(list 1600.3634 869.5058) 
(list 1600.37 869.5161) 
(list 1600.3783 869.5264) 
(list 1600.3879 869.5367) 
(list 1600.3987 869.5469) 
(list 1600.4102 869.5572) 
(list 1600.4222 869.5675) 
(list 1600.4343 869.5778) 
(list 1600.4461 869.5881) 
(list 1600.4573 869.5983) 
(list 1600.4675 869.6086) 
(list 1600.4763 869.6189) 
(list 1600.4836 869.6292) 
(list 1600.4891 869.6394) 
(list 1600.4926 869.6497) 
(list 1600.4939 869.66) 
(list 1600.4939 869.66)))
(apply 'command (append '("pline") coords '("c")))
(setq tap5 (ssadd (entlast) tap5))
(command "_mirror" (entlast) "" "1600,900" "1600,901" "No")
(setq tap5 (ssadd (entlast) tap5))
(setq coords (list 
(list 1601.126 869.29) 
(list 1600.4939 869.29) 
(list 1600.4939 869.3003) 
(list 1600.4939 869.3106) 
(list 1600.4939 869.3208) 
(list 1600.4939 869.3311) 
(list 1600.4939 869.3414) 
(list 1600.4939 869.3517) 
(list 1600.4939 869.3619) 
(list 1600.4939 869.3722) 
(list 1600.4939 869.3825) 
(list 1600.4939 869.3928) 
(list 1600.4939 869.4031) 
(list 1600.4939 869.4133) 
(list 1600.4939 869.4236) 
(list 1600.4939 869.4339) 
(list 1600.4939 869.4442) 
(list 1600.4939 869.4544) 
(list 1600.4939 869.4647) 
(list 1600.4939 869.475) 
(list 1600.4939 869.4853) 
(list 1600.4939 869.4956) 
(list 1600.4939 869.5058) 
(list 1600.4939 869.5161) 
(list 1600.4939 869.5264) 
(list 1600.4939 869.5367) 
(list 1600.4939 869.5469) 
(list 1600.4939 869.5572) 
(list 1600.4939 869.5675) 
(list 1600.4939 869.5778) 
(list 1600.4939 869.5881) 
(list 1600.4939 869.5983) 
(list 1600.4939 869.6086) 
(list 1600.4939 869.6189) 
(list 1600.4939 869.6292) 
(list 1600.4939 869.6394) 
(list 1600.4939 869.6497) 
(list 1600.4939 869.66) 
(list 1601.126 869.66)))
(apply 'command (append '("pline") coords '("c")))
(setq tap5 (ssadd (entlast) tap5))
(command "_mirror" (entlast) "" "1600,900" "1600,901" "No")
(setq tap5 (ssadd (entlast) tap5))
(setq coords (list 
(list 1600 869.66) 
(list 1600.135 869.66) 
(list 1600.135 869.6703) 
(list 1600.135 869.6806) 
(list 1600.135 869.6908) 
(list 1600.135 869.7011) 
(list 1600.135 869.7114) 
(list 1600.135 869.7217) 
(list 1600.135 869.7319) 
(list 1600.135 869.7422) 
(list 1600.135 869.7525) 
(list 1600.135 869.7628) 
(list 1600.135 869.7731) 
(list 1600.135 869.7833) 
(list 1600.135 869.7936) 
(list 1600.135 869.8039) 
(list 1600.135 869.8142) 
(list 1600.135 869.8244) 
(list 1600.135 869.8347) 
(list 1600.135 869.845) 
(list 1600.135 869.8553) 
(list 1600.135 869.8656) 
(list 1600.135 869.8758) 
(list 1600.135 869.8861) 
(list 1600.135 869.8964) 
(list 1600.135 869.9067) 
(list 1600.135 869.9169) 
(list 1600.135 869.9272) 
(list 1600.135 869.9375) 
(list 1600.135 869.9478) 
(list 1600.135 869.9581) 
(list 1600.135 869.9683) 
(list 1600.135 869.9786) 
(list 1600.135 869.9889) 
(list 1600.135 869.9992) 
(list 1600.135 870.0094) 
(list 1600.135 870.0197) 
(list 1600.135 870.03) 
(list 1600 870.03)))
(apply 'command (append '("pline") coords '("c")))
(setq tap5 (ssadd (entlast) tap5))
(command "_mirror" (entlast) "" "1600,900" "1600,901" "No")
(setq tap5 (ssadd (entlast) tap5))
(setq coords (list 
(list 1600.5038 869.66) 
(list 1600.4939 869.66) 
(list 1600.4931 869.6703) 
(list 1600.4901 869.6806) 
(list 1600.4851 869.6908) 
(list 1600.4781 869.7011) 
(list 1600.4693 869.7114) 
(list 1600.4591 869.7217) 
(list 1600.4477 869.7319) 
(list 1600.4354 869.7422) 
(list 1600.4227 869.7525) 
(list 1600.4099 869.7628) 
(list 1600.3974 869.7731) 
(list 1600.3856 869.7833) 
(list 1600.3748 869.7936) 
(list 1600.3654 869.8039) 
(list 1600.3577 869.8142) 
(list 1600.352 869.8244) 
(list 1600.3484 869.8347) 
(list 1600.347 869.845) 
(list 1600.3479 869.8553) 
(list 1600.3512 869.8656) 
(list 1600.3566 869.8758) 
(list 1600.3641 869.8861) 
(list 1600.3735 869.8964) 
(list 1600.3844 869.9067) 
(list 1600.3965 869.9169) 
(list 1600.4096 869.9272) 
(list 1600.4232 869.9375) 
(list 1600.4368 869.9478) 
(list 1600.4501 869.9581) 
(list 1600.4627 869.9683) 
(list 1600.4742 869.9786) 
(list 1600.4841 869.9889) 
(list 1600.4923 869.9992) 
(list 1600.4984 870.0094) 
(list 1600.5023 870.0197) 
(list 1600.5038 870.03) 
(list 1600.5038 870.03)))
(apply 'command (append '("pline") coords '("c")))
(setq tap5 (ssadd (entlast) tap5))
(command "_mirror" (entlast) "" "1600,900" "1600,901" "No")
(setq tap5 (ssadd (entlast) tap5))
(setq coords (list 
(list 1601.126 869.66) 
(list 1600.5038 869.66) 
(list 1600.5038 869.6703) 
(list 1600.5038 869.6806) 
(list 1600.5038 869.6908) 
(list 1600.5038 869.7011) 
(list 1600.5038 869.7114) 
(list 1600.5038 869.7217) 
(list 1600.5038 869.7319) 
(list 1600.5038 869.7422) 
(list 1600.5038 869.7525) 
(list 1600.5038 869.7628) 
(list 1600.5038 869.7731) 
(list 1600.5038 869.7833) 
(list 1600.5038 869.7936) 
(list 1600.5038 869.8039) 
(list 1600.5038 869.8142) 
(list 1600.5038 869.8244) 
(list 1600.5038 869.8347) 
(list 1600.5038 869.845) 
(list 1600.5038 869.8553) 
(list 1600.5038 869.8656) 
(list 1600.5038 869.8758) 
(list 1600.5038 869.8861) 
(list 1600.5038 869.8964) 
(list 1600.5038 869.9067) 
(list 1600.5038 869.9169) 
(list 1600.5038 869.9272) 
(list 1600.5038 869.9375) 
(list 1600.5038 869.9478) 
(list 1600.5038 869.9581) 
(list 1600.5038 869.9683) 
(list 1600.5038 869.9786) 
(list 1600.5038 869.9889) 
(list 1600.5038 869.9992) 
(list 1600.5038 870.0094) 
(list 1600.5038 870.0197) 
(list 1600.5038 870.03) 
(list 1601.126 870.03)))
(apply 'command (append '("pline") coords '("c")))
(setq tap5 (ssadd (entlast) tap5))
(command "_mirror" (entlast) "" "1600,900" "1600,901" "No")
(setq tap5 (ssadd (entlast) tap5))
(setq coords (list 
(list 1600 870.03) 
(list 1600.135 870.03) 
(list 1600.135 870.0403) 
(list 1600.135 870.0506) 
(list 1600.135 870.0608) 
(list 1600.135 870.0711) 
(list 1600.135 870.0814) 
(list 1600.135 870.0917) 
(list 1600.135 870.1019) 
(list 1600.135 870.1122) 
(list 1600.135 870.1225) 
(list 1600.135 870.1328) 
(list 1600.135 870.1431) 
(list 1600.135 870.1533) 
(list 1600.135 870.1636) 
(list 1600.135 870.1739) 
(list 1600.135 870.1842) 
(list 1600.135 870.1944) 
(list 1600.135 870.2047) 
(list 1600.135 870.215) 
(list 1600.135 870.2253) 
(list 1600.135 870.2356) 
(list 1600.135 870.2458) 
(list 1600.135 870.2561) 
(list 1600.135 870.2664) 
(list 1600.135 870.2767) 
(list 1600.135 870.2869) 
(list 1600.135 870.2972) 
(list 1600.135 870.3075) 
(list 1600.135 870.3178) 
(list 1600.135 870.3281) 
(list 1600.135 870.3383) 
(list 1600.135 870.3486) 
(list 1600.135 870.3589) 
(list 1600.135 870.3692) 
(list 1600.135 870.3794) 
(list 1600.135 870.3897) 
(list 1600.135 870.4) 
(list 1600 870.4)))
(apply 'command (append '("pline") coords '("c")))
(setq tap5 (ssadd (entlast) tap5))
(command "_mirror" (entlast) "" "1600,900" "1600,901" "No")
(setq tap5 (ssadd (entlast) tap5))
(setq coords (list 
(list 1600.5137 870.03) 
(list 1600.5038 870.03) 
(list 1600.5028 870.0403) 
(list 1600.4995 870.0506) 
(list 1600.4938 870.0608) 
(list 1600.4859 870.0711) 
(list 1600.476 870.0814) 
(list 1600.4645 870.0917) 
(list 1600.4517 870.1019) 
(list 1600.4379 870.1122) 
(list 1600.4236 870.1225) 
(list 1600.4093 870.1328) 
(list 1600.3953 870.1431) 
(list 1600.382 870.1533) 
(list 1600.37 870.1636) 
(list 1600.3595 870.1739) 
(list 1600.3509 870.1842) 
(list 1600.3445 870.1944) 
(list 1600.3405 870.2047) 
(list 1600.339 870.215) 
(list 1600.3401 870.2253) 
(list 1600.3437 870.2356) 
(list 1600.3498 870.2458) 
(list 1600.3582 870.2561) 
(list 1600.3686 870.2664) 
(list 1600.3808 870.2767) 
(list 1600.3944 870.2869) 
(list 1600.409 870.2972) 
(list 1600.4241 870.3075) 
(list 1600.4393 870.3178) 
(list 1600.4541 870.3281) 
(list 1600.4681 870.3383) 
(list 1600.4808 870.3486) 
(list 1600.4919 870.3589) 
(list 1600.501 870.3692) 
(list 1600.5078 870.3794) 
(list 1600.512 870.3897) 
(list 1600.5137 870.4) 
(list 1600.5137 870.4)))
(apply 'command (append '("pline") coords '("c")))
(setq tap5 (ssadd (entlast) tap5))
(command "_mirror" (entlast) "" "1600,900" "1600,901" "No")
(setq tap5 (ssadd (entlast) tap5))
(setq coords (list 
(list 1601.126 870.03) 
(list 1600.5137 870.03) 
(list 1600.5137 870.0403) 
(list 1600.5137 870.0506) 
(list 1600.5137 870.0608) 
(list 1600.5137 870.0711) 
(list 1600.5137 870.0814) 
(list 1600.5137 870.0917) 
(list 1600.5137 870.1019) 
(list 1600.5137 870.1122) 
(list 1600.5137 870.1225) 
(list 1600.5137 870.1328) 
(list 1600.5137 870.1431) 
(list 1600.5137 870.1533) 
(list 1600.5137 870.1636) 
(list 1600.5137 870.1739) 
(list 1600.5137 870.1842) 
(list 1600.5137 870.1944) 
(list 1600.5137 870.2047) 
(list 1600.5137 870.215) 
(list 1600.5137 870.2253) 
(list 1600.5137 870.2356) 
(list 1600.5137 870.2458) 
(list 1600.5137 870.2561) 
(list 1600.5137 870.2664) 
(list 1600.5137 870.2767) 
(list 1600.5137 870.2869) 
(list 1600.5137 870.2972) 
(list 1600.5137 870.3075) 
(list 1600.5137 870.3178) 
(list 1600.5137 870.3281) 
(list 1600.5137 870.3383) 
(list 1600.5137 870.3486) 
(list 1600.5137 870.3589) 
(list 1600.5137 870.3692) 
(list 1600.5137 870.3794) 
(list 1600.5137 870.3897) 
(list 1600.5137 870.4) 
(list 1601.126 870.4)))
(apply 'command (append '("pline") coords '("c")))
(setq tap5 (ssadd (entlast) tap5))
(command "_mirror" (entlast) "" "1600,900" "1600,901" "No")
(setq tap5 (ssadd (entlast) tap5))
(setq coords (list 
(list 1600 870.4) 
(list 1600.135 870.4) 
(list 1600.135 870.4103) 
(list 1600.135 870.4206) 
(list 1600.135 870.4308) 
(list 1600.135 870.4411) 
(list 1600.135 870.4514) 
(list 1600.135 870.4617) 
(list 1600.135 870.4719) 
(list 1600.135 870.4822) 
(list 1600.135 870.4925) 
(list 1600.135 870.5028) 
(list 1600.135 870.5131) 
(list 1600.135 870.5233) 
(list 1600.135 870.5336) 
(list 1600.135 870.5439) 
(list 1600.135 870.5542) 
(list 1600.135 870.5644) 
(list 1600.135 870.5747) 
(list 1600.135 870.585) 
(list 1600.135 870.5953) 
(list 1600.135 870.6056) 
(list 1600.135 870.6158) 
(list 1600.135 870.6261) 
(list 1600.135 870.6364) 
(list 1600.135 870.6467) 
(list 1600.135 870.6569) 
(list 1600.135 870.6672) 
(list 1600.135 870.6775) 
(list 1600.135 870.6878) 
(list 1600.135 870.6981) 
(list 1600.135 870.7083) 
(list 1600.135 870.7186) 
(list 1600.135 870.7289) 
(list 1600.135 870.7392) 
(list 1600.135 870.7494) 
(list 1600.135 870.7597) 
(list 1600.135 870.77) 
(list 1600 870.77)))
(apply 'command (append '("pline") coords '("c")))
(setq tap5 (ssadd (entlast) tap5))
(command "_mirror" (entlast) "" "1600,900" "1600,901" "No")
(setq tap5 (ssadd (entlast) tap5))
(setq coords (list 
(list 1600.5235 870.4) 
(list 1600.5137 870.4) 
(list 1600.5126 870.4103) 
(list 1600.5088 870.4206) 
(list 1600.5024 870.4308) 
(list 1600.4936 870.4411) 
(list 1600.4827 870.4514) 
(list 1600.4699 870.4617) 
(list 1600.4557 870.4719) 
(list 1600.4404 870.4822) 
(list 1600.4246 870.4925) 
(list 1600.4086 870.5028) 
(list 1600.3931 870.5131) 
(list 1600.3785 870.5233) 
(list 1600.3652 870.5336) 
(list 1600.3536 870.5439) 
(list 1600.3441 870.5542) 
(list 1600.3371 870.5644) 
(list 1600.3326 870.5747) 
(list 1600.331 870.585) 
(list 1600.3322 870.5953) 
(list 1600.3362 870.6056) 
(list 1600.343 870.6158) 
(list 1600.3523 870.6261) 
(list 1600.3638 870.6364) 
(list 1600.3773 870.6467) 
(list 1600.3923 870.6569) 
(list 1600.4084 870.6672) 
(list 1600.425 870.6775) 
(list 1600.4418 870.6878) 
(list 1600.4581 870.6981) 
(list 1600.4735 870.7083) 
(list 1600.4875 870.7186) 
(list 1600.4997 870.7289) 
(list 1600.5096 870.7392) 
(list 1600.5171 870.7494) 
(list 1600.5218 870.7597) 
(list 1600.5235 870.77) 
(list 1600.5235 870.77)))
(apply 'command (append '("pline") coords '("c")))
(setq tap5 (ssadd (entlast) tap5))
(command "_mirror" (entlast) "" "1600,900" "1600,901" "No")
(setq tap5 (ssadd (entlast) tap5))
(setq coords (list 
(list 1601.126 870.4) 
(list 1600.5235 870.4) 
(list 1600.5235 870.4103) 
(list 1600.5235 870.4206) 
(list 1600.5235 870.4308) 
(list 1600.5235 870.4411) 
(list 1600.5235 870.4514) 
(list 1600.5235 870.4617) 
(list 1600.5235 870.4719) 
(list 1600.5235 870.4822) 
(list 1600.5235 870.4925) 
(list 1600.5235 870.5028) 
(list 1600.5235 870.5131) 
(list 1600.5235 870.5233) 
(list 1600.5235 870.5336) 
(list 1600.5235 870.5439) 
(list 1600.5235 870.5542) 
(list 1600.5235 870.5644) 
(list 1600.5235 870.5747) 
(list 1600.5235 870.585) 
(list 1600.5235 870.5953) 
(list 1600.5235 870.6056) 
(list 1600.5235 870.6158) 
(list 1600.5235 870.6261) 
(list 1600.5235 870.6364) 
(list 1600.5235 870.6467) 
(list 1600.5235 870.6569) 
(list 1600.5235 870.6672) 
(list 1600.5235 870.6775) 
(list 1600.5235 870.6878) 
(list 1600.5235 870.6981) 
(list 1600.5235 870.7083) 
(list 1600.5235 870.7186) 
(list 1600.5235 870.7289) 
(list 1600.5235 870.7392) 
(list 1600.5235 870.7494) 
(list 1600.5235 870.7597) 
(list 1600.5235 870.77) 
(list 1601.126 870.77)))
(apply 'command (append '("pline") coords '("c")))
(setq tap5 (ssadd (entlast) tap5))
(command "_mirror" (entlast) "" "1600,900" "1600,901" "No")
(setq tap5 (ssadd (entlast) tap5))
(setq coords (list 
(list 1600 870.77) 
(list 1600.135 870.77) 
(list 1600.135 870.7803) 
(list 1600.135 870.7906) 
(list 1600.135 870.8008) 
(list 1600.135 870.8111) 
(list 1600.135 870.8214) 
(list 1600.135 870.8317) 
(list 1600.135 870.8419) 
(list 1600.135 870.8522) 
(list 1600.135 870.8625) 
(list 1600.135 870.8728) 
(list 1600.135 870.8831) 
(list 1600.135 870.8933) 
(list 1600.135 870.9036) 
(list 1600.135 870.9139) 
(list 1600.135 870.9242) 
(list 1600.135 870.9344) 
(list 1600.135 870.9447) 
(list 1600.135 870.955) 
(list 1600.135 870.9653) 
(list 1600.135 870.9756) 
(list 1600.135 870.9858) 
(list 1600.135 870.9961) 
(list 1600.135 871.0064) 
(list 1600.135 871.0167) 
(list 1600.135 871.0269) 
(list 1600.135 871.0372) 
(list 1600.135 871.0475) 
(list 1600.135 871.0578) 
(list 1600.135 871.0681) 
(list 1600.135 871.0783) 
(list 1600.135 871.0886) 
(list 1600.135 871.0989) 
(list 1600.135 871.1092) 
(list 1600.135 871.1194) 
(list 1600.135 871.1297) 
(list 1600.135 871.14) 
(list 1600 871.14)))
(apply 'command (append '("pline") coords '("c")))
(setq tap5 (ssadd (entlast) tap5))
(command "_mirror" (entlast) "" "1600,900" "1600,901" "No")
(setq tap5 (ssadd (entlast) tap5))
(setq coords (list 
(list 1600.5334 870.77) 
(list 1600.5235 870.77) 
(list 1600.5223 870.7803) 
(list 1600.5181 870.7906) 
(list 1600.5111 870.8008) 
(list 1600.5014 870.8111) 
(list 1600.4894 870.8214) 
(list 1600.4753 870.8317) 
(list 1600.4597 870.8419) 
(list 1600.4429 870.8522) 
(list 1600.4255 870.8625) 
(list 1600.408 870.8728) 
(list 1600.391 870.8831) 
(list 1600.375 870.8933) 
(list 1600.3604 870.9036) 
(list 1600.3477 870.9139) 
(list 1600.3373 870.9242) 
(list 1600.3296 870.9344) 
(list 1600.3248 870.9447) 
(list 1600.323 870.955) 
(list 1600.3243 870.9653) 
(list 1600.3288 870.9756) 
(list 1600.3362 870.9858) 
(list 1600.3464 870.9961) 
(list 1600.359 871.0064) 
(list 1600.3738 871.0167) 
(list 1600.3902 871.0269) 
(list 1600.4078 871.0372) 
(list 1600.426 871.0475) 
(list 1600.4443 871.0578) 
(list 1600.4621 871.0681) 
(list 1600.4789 871.0783) 
(list 1600.4942 871.0886) 
(list 1600.5075 871.0989) 
(list 1600.5183 871.1092) 
(list 1600.5264 871.1194) 
(list 1600.5315 871.1297) 
(list 1600.5334 871.14) 
(list 1600.5334 871.14)))
(apply 'command (append '("pline") coords '("c")))
(setq tap5 (ssadd (entlast) tap5))
(command "_mirror" (entlast) "" "1600,900" "1600,901" "No")
(setq tap5 (ssadd (entlast) tap5))
(setq coords (list 
(list 1601.126 870.77) 
(list 1600.5334 870.77) 
(list 1600.5334 870.7803) 
(list 1600.5334 870.7906) 
(list 1600.5334 870.8008) 
(list 1600.5334 870.8111) 
(list 1600.5334 870.8214) 
(list 1600.5334 870.8317) 
(list 1600.5334 870.8419) 
(list 1600.5334 870.8522) 
(list 1600.5334 870.8625) 
(list 1600.5334 870.8728) 
(list 1600.5334 870.8831) 
(list 1600.5334 870.8933) 
(list 1600.5334 870.9036) 
(list 1600.5334 870.9139) 
(list 1600.5334 870.9242) 
(list 1600.5334 870.9344) 
(list 1600.5334 870.9447) 
(list 1600.5334 870.955) 
(list 1600.5334 870.9653) 
(list 1600.5334 870.9756) 
(list 1600.5334 870.9858) 
(list 1600.5334 870.9961) 
(list 1600.5334 871.0064) 
(list 1600.5334 871.0167) 
(list 1600.5334 871.0269) 
(list 1600.5334 871.0372) 
(list 1600.5334 871.0475) 
(list 1600.5334 871.0578) 
(list 1600.5334 871.0681) 
(list 1600.5334 871.0783) 
(list 1600.5334 871.0886) 
(list 1600.5334 871.0989) 
(list 1600.5334 871.1092) 
(list 1600.5334 871.1194) 
(list 1600.5334 871.1297) 
(list 1600.5334 871.14) 
(list 1601.126 871.14)))
(apply 'command (append '("pline") coords '("c")))
(setq tap5 (ssadd (entlast) tap5))
(command "_mirror" (entlast) "" "1600,900" "1600,901" "No")
(setq tap5 (ssadd (entlast) tap5))
(setq coords (list 
(list 1600 871.14) 
(list 1600.135 871.14) 
(list 1600.135 871.1503) 
(list 1600.135 871.1606) 
(list 1600.135 871.1708) 
(list 1600.135 871.1811) 
(list 1600.135 871.1914) 
(list 1600.135 871.2017) 
(list 1600.135 871.2119) 
(list 1600.135 871.2222) 
(list 1600.135 871.2325) 
(list 1600.135 871.2428) 
(list 1600.135 871.2531) 
(list 1600.135 871.2633) 
(list 1600.135 871.2736) 
(list 1600.135 871.2839) 
(list 1600.135 871.2942) 
(list 1600.135 871.3044) 
(list 1600.135 871.3147) 
(list 1600.135 871.325) 
(list 1600.135 871.3353) 
(list 1600.135 871.3456) 
(list 1600.135 871.3558) 
(list 1600.135 871.3661) 
(list 1600.135 871.3764) 
(list 1600.135 871.3867) 
(list 1600.135 871.3969) 
(list 1600.135 871.4072) 
(list 1600.135 871.4175) 
(list 1600.135 871.4278) 
(list 1600.135 871.4381) 
(list 1600.135 871.4483) 
(list 1600.135 871.4586) 
(list 1600.135 871.4689) 
(list 1600.135 871.4792) 
(list 1600.135 871.4894) 
(list 1600.135 871.4997) 
(list 1600.135 871.51) 
(list 1600 871.51)))
(apply 'command (append '("pline") coords '("c")))
(setq tap5 (ssadd (entlast) tap5))
(command "_mirror" (entlast) "" "1600,900" "1600,901" "No")
(setq tap5 (ssadd (entlast) tap5))
(setq coords (list 
(list 1600.5433 871.14) 
(list 1600.5334 871.14) 
(list 1600.532 871.1503) 
(list 1600.5275 871.1606) 
(list 1600.5198 871.1708) 
(list 1600.5092 871.1811) 
(list 1600.496 871.1914) 
(list 1600.4807 871.2017) 
(list 1600.4636 871.2119) 
(list 1600.4454 871.2222) 
(list 1600.4264 871.2325) 
(list 1600.4074 871.2428) 
(list 1600.3889 871.2531) 
(list 1600.3714 871.2633) 
(list 1600.3556 871.2736) 
(list 1600.3418 871.2839) 
(list 1600.3305 871.2942) 
(list 1600.3221 871.3044) 
(list 1600.3169 871.3147) 
(list 1600.315 871.325) 
(list 1600.3165 871.3353) 
(list 1600.3213 871.3456) 
(list 1600.3294 871.3558) 
(list 1600.3405 871.3661) 
(list 1600.3542 871.3764) 
(list 1600.3702 871.3867) 
(list 1600.3881 871.3969) 
(list 1600.4071 871.4072) 
(list 1600.4269 871.4175) 
(list 1600.4467 871.4278) 
(list 1600.4661 871.4381) 
(list 1600.4843 871.4483) 
(list 1600.5009 871.4586) 
(list 1600.5152 871.4689) 
(list 1600.527 871.4792) 
(list 1600.5357 871.4894) 
(list 1600.5412 871.4997) 
(list 1600.5433 871.51) 
(list 1600.5433 871.51)))
(apply 'command (append '("pline") coords '("c")))
(setq tap5 (ssadd (entlast) tap5))
(command "_mirror" (entlast) "" "1600,900" "1600,901" "No")
(setq tap5 (ssadd (entlast) tap5))
(setq coords (list 
(list 1601.126 871.14) 
(list 1600.5433 871.14) 
(list 1600.5433 871.1503) 
(list 1600.5433 871.1606) 
(list 1600.5433 871.1708) 
(list 1600.5433 871.1811) 
(list 1600.5433 871.1914) 
(list 1600.5433 871.2017) 
(list 1600.5433 871.2119) 
(list 1600.5433 871.2222) 
(list 1600.5433 871.2325) 
(list 1600.5433 871.2428) 
(list 1600.5433 871.2531) 
(list 1600.5433 871.2633) 
(list 1600.5433 871.2736) 
(list 1600.5433 871.2839) 
(list 1600.5433 871.2942) 
(list 1600.5433 871.3044) 
(list 1600.5433 871.3147) 
(list 1600.5433 871.325) 
(list 1600.5433 871.3353) 
(list 1600.5433 871.3456) 
(list 1600.5433 871.3558) 
(list 1600.5433 871.3661) 
(list 1600.5433 871.3764) 
(list 1600.5433 871.3867) 
(list 1600.5433 871.3969) 
(list 1600.5433 871.4072) 
(list 1600.5433 871.4175) 
(list 1600.5433 871.4278) 
(list 1600.5433 871.4381) 
(list 1600.5433 871.4483) 
(list 1600.5433 871.4586) 
(list 1600.5433 871.4689) 
(list 1600.5433 871.4792) 
(list 1600.5433 871.4894) 
(list 1600.5433 871.4997) 
(list 1600.5433 871.51) 
(list 1601.126 871.51)))
(apply 'command (append '("pline") coords '("c")))
(setq tap5 (ssadd (entlast) tap5))
(command "_mirror" (entlast) "" "1600,900" "1600,901" "No")
(setq tap5 (ssadd (entlast) tap5))
(setq coords (list 
(list 1600 871.51) 
(list 1600.135 871.51) 
(list 1600.135 871.5203) 
(list 1600.135 871.5306) 
(list 1600.135 871.5408) 
(list 1600.135 871.5511) 
(list 1600.135 871.5614) 
(list 1600.135 871.5717) 
(list 1600.135 871.5819) 
(list 1600.135 871.5922) 
(list 1600.135 871.6025) 
(list 1600.135 871.6128) 
(list 1600.135 871.6231) 
(list 1600.135 871.6333) 
(list 1600.135 871.6436) 
(list 1600.135 871.6539) 
(list 1600.135 871.6642) 
(list 1600.135 871.6744) 
(list 1600.135 871.6847) 
(list 1600.135 871.695) 
(list 1600.135 871.7053) 
(list 1600.135 871.7156) 
(list 1600.135 871.7258) 
(list 1600.135 871.7361) 
(list 1600.135 871.7464) 
(list 1600.135 871.7567) 
(list 1600.135 871.7669) 
(list 1600.135 871.7772) 
(list 1600.135 871.7875) 
(list 1600.135 871.7978) 
(list 1600.135 871.8081) 
(list 1600.135 871.8183) 
(list 1600.135 871.8286) 
(list 1600.135 871.8389) 
(list 1600.135 871.8492) 
(list 1600.135 871.8594) 
(list 1600.135 871.8697) 
(list 1600.135 871.88) 
(list 1600 871.88)))
(apply 'command (append '("pline") coords '("c")))
(setq tap5 (ssadd (entlast) tap5))
(command "_mirror" (entlast) "" "1600,900" "1600,901" "No")
(setq tap5 (ssadd (entlast) tap5))
(setq coords (list 
(list 1600.5531 871.51) 
(list 1600.5433 871.51) 
(list 1600.5418 871.5203) 
(list 1600.5368 871.5306) 
(list 1600.5284 871.5408) 
(list 1600.517 871.5511) 
(list 1600.5027 871.5614) 
(list 1600.4861 871.5717) 
(list 1600.4676 871.5819) 
(list 1600.4479 871.5922) 
(list 1600.4274 871.6025) 
(list 1600.4068 871.6128) 
(list 1600.3868 871.6231) 
(list 1600.3679 871.6333) 
(list 1600.3507 871.6436) 
(list 1600.3359 871.6539) 
(list 1600.3237 871.6642) 
(list 1600.3147 871.6744) 
(list 1600.3091 871.6847) 
(list 1600.307 871.695) 
(list 1600.3086 871.7053) 
(list 1600.3139 871.7156) 
(list 1600.3226 871.7258) 
(list 1600.3346 871.7361) 
(list 1600.3494 871.7464) 
(list 1600.3667 871.7567) 
(list 1600.3859 871.7669) 
(list 1600.4065 871.7772) 
(list 1600.4278 871.7875) 
(list 1600.4492 871.7978) 
(list 1600.4701 871.8081) 
(list 1600.4897 871.8183) 
(list 1600.5075 871.8286) 
(list 1600.523 871.8389) 
(list 1600.5357 871.8492) 
(list 1600.5451 871.8594) 
(list 1600.551 871.8697) 
(list 1600.5531 871.88) 
(list 1600.5531 871.88)))
(apply 'command (append '("pline") coords '("c")))
(setq tap5 (ssadd (entlast) tap5))
(command "_mirror" (entlast) "" "1600,900" "1600,901" "No")
(setq tap5 (ssadd (entlast) tap5))
(setq coords (list 
(list 1601.126 871.51) 
(list 1600.5531 871.51) 
(list 1600.5531 871.5203) 
(list 1600.5531 871.5306) 
(list 1600.5531 871.5408) 
(list 1600.5531 871.5511) 
(list 1600.5531 871.5614) 
(list 1600.5531 871.5717) 
(list 1600.5531 871.5819) 
(list 1600.5531 871.5922) 
(list 1600.5531 871.6025) 
(list 1600.5531 871.6128) 
(list 1600.5531 871.6231) 
(list 1600.5531 871.6333) 
(list 1600.5531 871.6436) 
(list 1600.5531 871.6539) 
(list 1600.5531 871.6642) 
(list 1600.5531 871.6744) 
(list 1600.5531 871.6847) 
(list 1600.5531 871.695) 
(list 1600.5531 871.7053) 
(list 1600.5531 871.7156) 
(list 1600.5531 871.7258) 
(list 1600.5531 871.7361) 
(list 1600.5531 871.7464) 
(list 1600.5531 871.7567) 
(list 1600.5531 871.7669) 
(list 1600.5531 871.7772) 
(list 1600.5531 871.7875) 
(list 1600.5531 871.7978) 
(list 1600.5531 871.8081) 
(list 1600.5531 871.8183) 
(list 1600.5531 871.8286) 
(list 1600.5531 871.8389) 
(list 1600.5531 871.8492) 
(list 1600.5531 871.8594) 
(list 1600.5531 871.8697) 
(list 1600.5531 871.88) 
(list 1601.126 871.88)))
(apply 'command (append '("pline") coords '("c")))
(setq tap5 (ssadd (entlast) tap5))
(command "_mirror" (entlast) "" "1600,900" "1600,901" "No")
(setq tap5 (ssadd (entlast) tap5))
(setq coords (list 
(list 1600 871.88) 
(list 1600.135 871.88) 
(list 1600.135 871.8903) 
(list 1600.135 871.9006) 
(list 1600.135 871.9108) 
(list 1600.135 871.9211) 
(list 1600.135 871.9314) 
(list 1600.135 871.9417) 
(list 1600.135 871.9519) 
(list 1600.135 871.9622) 
(list 1600.135 871.9725) 
(list 1600.135 871.9828) 
(list 1600.135 871.9931) 
(list 1600.135 872.0033) 
(list 1600.135 872.0136) 
(list 1600.135 872.0239) 
(list 1600.135 872.0342) 
(list 1600.135 872.0444) 
(list 1600.135 872.0547) 
(list 1600.135 872.065) 
(list 1600.135 872.0753) 
(list 1600.135 872.0856) 
(list 1600.135 872.0958) 
(list 1600.135 872.1061) 
(list 1600.135 872.1164) 
(list 1600.135 872.1267) 
(list 1600.135 872.1369) 
(list 1600.135 872.1472) 
(list 1600.135 872.1575) 
(list 1600.135 872.1678) 
(list 1600.135 872.1781) 
(list 1600.135 872.1883) 
(list 1600.135 872.1986) 
(list 1600.135 872.2089) 
(list 1600.135 872.2192) 
(list 1600.135 872.2294) 
(list 1600.135 872.2397) 
(list 1600.135 872.25) 
(list 1600 872.25)))
(apply 'command (append '("pline") coords '("c")))
(setq tap5 (ssadd (entlast) tap5))
(command "_mirror" (entlast) "" "1600,900" "1600,901" "No")
(setq tap5 (ssadd (entlast) tap5))
(setq coords (list 
(list 1600.563 871.88) 
(list 1600.5531 871.88) 
(list 1600.5515 871.8903) 
(list 1600.5461 871.9006) 
(list 1600.5371 871.9108) 
(list 1600.5247 871.9211) 
(list 1600.5094 871.9314) 
(list 1600.4915 871.9417) 
(list 1600.4716 871.9519) 
(list 1600.4503 871.9622) 
(list 1600.4283 871.9725) 
(list 1600.4062 871.9828) 
(list 1600.3846 871.9931) 
(list 1600.3644 872.0033) 
(list 1600.3459 872.0136) 
(list 1600.33 872.0239) 
(list 1600.3169 872.0342) 
(list 1600.3072 872.0444) 
(list 1600.3012 872.0547) 
(list 1600.299 872.065) 
(list 1600.3008 872.0753) 
(list 1600.3064 872.0856) 
(list 1600.3158 872.0958) 
(list 1600.3286 872.1061) 
(list 1600.3446 872.1164) 
(list 1600.3632 872.1267) 
(list 1600.3838 872.1369) 
(list 1600.4059 872.1472) 
(list 1600.4288 872.1575) 
(list 1600.4517 872.1678) 
(list 1600.4741 872.1781) 
(list 1600.4951 872.1883) 
(list 1600.5142 872.1986) 
(list 1600.5308 872.2089) 
(list 1600.5443 872.2192) 
(list 1600.5544 872.2294) 
(list 1600.5607 872.2397) 
(list 1600.563 872.25) 
(list 1600.563 872.25)))
(apply 'command (append '("pline") coords '("c")))
(setq tap5 (ssadd (entlast) tap5))
(command "_mirror" (entlast) "" "1600,900" "1600,901" "No")
(setq tap5 (ssadd (entlast) tap5))
(setq coords (list 
(list 1601.126 871.88) 
(list 1600.563 871.88) 
(list 1600.563 871.8903) 
(list 1600.563 871.9006) 
(list 1600.563 871.9108) 
(list 1600.563 871.9211) 
(list 1600.563 871.9314) 
(list 1600.563 871.9417) 
(list 1600.563 871.9519) 
(list 1600.563 871.9622) 
(list 1600.563 871.9725) 
(list 1600.563 871.9828) 
(list 1600.563 871.9931) 
(list 1600.563 872.0033) 
(list 1600.563 872.0136) 
(list 1600.563 872.0239) 
(list 1600.563 872.0342) 
(list 1600.563 872.0444) 
(list 1600.563 872.0547) 
(list 1600.563 872.065) 
(list 1600.563 872.0753) 
(list 1600.563 872.0856) 
(list 1600.563 872.0958) 
(list 1600.563 872.1061) 
(list 1600.563 872.1164) 
(list 1600.563 872.1267) 
(list 1600.563 872.1369) 
(list 1600.563 872.1472) 
(list 1600.563 872.1575) 
(list 1600.563 872.1678) 
(list 1600.563 872.1781) 
(list 1600.563 872.1883) 
(list 1600.563 872.1986) 
(list 1600.563 872.2089) 
(list 1600.563 872.2192) 
(list 1600.563 872.2294) 
(list 1600.563 872.2397) 
(list 1600.563 872.25) 
(list 1601.126 872.25)))
(apply 'command (append '("pline") coords '("c")))
(setq tap5 (ssadd (entlast) tap5))
(command "_mirror" (entlast) "" "1600,900" "1600,901" "No")
(setq tap5 (ssadd (entlast) tap5))
(command "_block" "blktap5" "1600,900" tap5 "")
(command "_insert" "blktap5" "1600,900" "1" "1" "0")
(command "_insert" "blktap5" "1600,900" "1" "1" "180")
(setq uc5 nil)
(setq uc5 (ssadd))
(setq coords (list 
(list 0 -0.185) 
(list 0.135 -0.185) 
(list 0.135 -0.17472) 
(list 0.135 -0.16444) 
(list 0.135 -0.15417) 
(list 0.135 -0.14389) 
(list 0.135 -0.13361) 
(list 0.135 -0.12333) 
(list 0.135 -0.11306) 
(list 0.135 -0.10278) 
(list 0.135 -0.0925) 
(list 0.135 -0.082222) 
(list 0.135 -0.071944) 
(list 0.135 -0.061667) 
(list 0.135 -0.051389) 
(list 0.135 -0.041111) 
(list 0.135 -0.030833) 
(list 0.135 -0.020556) 
(list 0.135 -0.010278) 
(list 0.135 0) 
(list 0.135 0.010278) 
(list 0.135 0.020556) 
(list 0.135 0.030833) 
(list 0.135 0.041111) 
(list 0.135 0.051389) 
(list 0.135 0.061667) 
(list 0.135 0.071944) 
(list 0.135 0.082222) 
(list 0.135 0.0925) 
(list 0.135 0.10278) 
(list 0.135 0.11306) 
(list 0.135 0.12333) 
(list 0.135 0.13361) 
(list 0.135 0.14389) 
(list 0.135 0.15417) 
(list 0.135 0.16444) 
(list 0.135 0.17472) 
(list 0.135 0.185) 
(list 0 0.185)))
(apply 'command (append '("pline") coords '("c")))
(setq uc5 (ssadd (entlast) uc5))
(setq coords (list 
(list 1.126 -0.185) 
(list 0.563 -0.185) 
(list 0.56096 -0.17472) 
(list 0.55492 -0.16444) 
(list 0.54505 -0.15417) 
(list 0.53165 -0.14389) 
(list 0.51513 -0.13361) 
(list 0.496 -0.12333) 
(list 0.47483 -0.11306) 
(list 0.45227 -0.10278) 
(list 0.429 -0.0925) 
(list 0.40573 -0.082222) 
(list 0.38317 -0.071944) 
(list 0.362 -0.061667) 
(list 0.34287 -0.051389) 
(list 0.32635 -0.041111) 
(list 0.31295 -0.030833) 
(list 0.30308 -0.020556) 
(list 0.29704 -0.010278) 
(list 0.295 0) 
(list 0.29704 0.010278) 
(list 0.30308 0.020556) 
(list 0.31295 0.030833) 
(list 0.32635 0.041111) 
(list 0.34287 0.051389) 
(list 0.362 0.061667) 
(list 0.38317 0.071944) 
(list 0.40573 0.082222) 
(list 0.429 0.0925) 
(list 0.45227 0.10278) 
(list 0.47483 0.11306) 
(list 0.496 0.12333) 
(list 0.51513 0.13361) 
(list 0.53165 0.14389) 
(list 0.54505 0.15417) 
(list 0.55492 0.16444) 
(list 0.56096 0.17472) 
(list 0.563 0.185) 
(list 1.126 0.185)))
(apply 'command (append '("pline") coords '("c")))
(setq uc5 (ssadd (entlast) uc5))
(command "_block" "blkuc5" "0,0.185" uc5 "")
(command "_insert" "blkuc5" "1600,872.62" "1" "1" "0")
(command "_insert" "blkuc5" "1600,872.25" "1" "1" "180")
(command "_insert" "blkuc5" "1600,872.99" "1" "1" "0")
(command "_insert" "blkuc5" "1600,872.62" "1" "1" "180")
(command "_insert" "blkuc5" "1600,873.36" "1" "1" "0")
(command "_insert" "blkuc5" "1600,872.99" "1" "1" "180")
(command "_insert" "blkuc5" "1600,873.73" "1" "1" "0")
(command "_insert" "blkuc5" "1600,873.36" "1" "1" "180")
(command "_insert" "blkuc5" "1600,874.1" "1" "1" "0")
(command "_insert" "blkuc5" "1600,873.73" "1" "1" "180")
(command "_insert" "blkuc5" "1600,874.47" "1" "1" "0")
(command "_insert" "blkuc5" "1600,874.1" "1" "1" "180")
(command "_insert" "blkuc5" "1600,874.84" "1" "1" "0")
(command "_insert" "blkuc5" "1600,874.47" "1" "1" "180")
(command "_insert" "blkuc5" "1600,875.21" "1" "1" "0")
(command "_insert" "blkuc5" "1600,874.84" "1" "1" "180")
(command "_insert" "blkuc5" "1600,875.58" "1" "1" "0")
(command "_insert" "blkuc5" "1600,875.21" "1" "1" "180")
(command "_insert" "blkuc5" "1600,875.95" "1" "1" "0")
(command "_insert" "blkuc5" "1600,875.58" "1" "1" "180")
(command "_insert" "blkuc5" "1600,876.32" "1" "1" "0")
(command "_insert" "blkuc5" "1600,875.95" "1" "1" "180")
(command "_insert" "blkuc5" "1600,876.69" "1" "1" "0")
(command "_insert" "blkuc5" "1600,876.32" "1" "1" "180")
(command "_insert" "blkuc5" "1600,877.06" "1" "1" "0")
(command "_insert" "blkuc5" "1600,876.69" "1" "1" "180")
(command "_insert" "blkuc5" "1600,877.43" "1" "1" "0")
(command "_insert" "blkuc5" "1600,877.06" "1" "1" "180")
(command "_insert" "blkuc5" "1600,877.8" "1" "1" "0")
(command "_insert" "blkuc5" "1600,877.43" "1" "1" "180")
(command "_insert" "blkuc5" "1600,878.17" "1" "1" "0")
(command "_insert" "blkuc5" "1600,877.8" "1" "1" "180")
(command "_insert" "blkuc5" "1600,878.54" "1" "1" "0")
(command "_insert" "blkuc5" "1600,878.17" "1" "1" "180")
(command "_insert" "blkuc5" "1600,878.91" "1" "1" "0")
(command "_insert" "blkuc5" "1600,878.54" "1" "1" "180")
(command "_insert" "blkuc5" "1600,879.28" "1" "1" "0")
(command "_insert" "blkuc5" "1600,878.91" "1" "1" "180")
(command "_insert" "blkuc5" "1600,879.65" "1" "1" "0")
(command "_insert" "blkuc5" "1600,879.28" "1" "1" "180")
(command "_insert" "blkuc5" "1600,880.02" "1" "1" "0")
(command "_insert" "blkuc5" "1600,879.65" "1" "1" "180")
(command "_insert" "blkuc5" "1600,880.39" "1" "1" "0")
(command "_insert" "blkuc5" "1600,880.02" "1" "1" "180")
(command "_insert" "blkuc5" "1600,880.76" "1" "1" "0")
(command "_insert" "blkuc5" "1600,880.39" "1" "1" "180")
(command "_insert" "blkuc5" "1600,881.13" "1" "1" "0")
(command "_insert" "blkuc5" "1600,880.76" "1" "1" "180")
(command "_insert" "blkuc5" "1600,881.5" "1" "1" "0")
(command "_insert" "blkuc5" "1600,881.13" "1" "1" "180")
(command "_insert" "blkuc5" "1600,881.87" "1" "1" "0")
(command "_insert" "blkuc5" "1600,881.5" "1" "1" "180")
(command "_insert" "blkuc5" "1600,882.24" "1" "1" "0")
(command "_insert" "blkuc5" "1600,881.87" "1" "1" "180")
(command "_insert" "blkuc5" "1600,882.61" "1" "1" "0")
(command "_insert" "blkuc5" "1600,882.24" "1" "1" "180")
(command "_insert" "blkuc5" "1600,882.98" "1" "1" "0")
(command "_insert" "blkuc5" "1600,882.61" "1" "1" "180")
(command "_insert" "blkuc5" "1600,883.35" "1" "1" "0")
(command "_insert" "blkuc5" "1600,882.98" "1" "1" "180")
(command "_insert" "blkuc5" "1600,883.72" "1" "1" "0")
(command "_insert" "blkuc5" "1600,883.35" "1" "1" "180")
(command "_insert" "blkuc5" "1600,884.09" "1" "1" "0")
(command "_insert" "blkuc5" "1600,883.72" "1" "1" "180")
(command "_insert" "blkuc5" "1600,884.46" "1" "1" "0")
(command "_insert" "blkuc5" "1600,884.09" "1" "1" "180")
(command "_insert" "blkuc5" "1600,884.83" "1" "1" "0")
(command "_insert" "blkuc5" "1600,884.46" "1" "1" "180")
(command "_insert" "blkuc5" "1600,885.2" "1" "1" "0")
(command "_insert" "blkuc5" "1600,884.83" "1" "1" "180")
(command "_insert" "blkuc5" "1600,885.57" "1" "1" "0")
(command "_insert" "blkuc5" "1600,885.2" "1" "1" "180")
(command "_insert" "blkuc5" "1600,885.94" "1" "1" "0")
(command "_insert" "blkuc5" "1600,885.57" "1" "1" "180")
(command "_insert" "blkuc5" "1600,886.31" "1" "1" "0")
(command "_insert" "blkuc5" "1600,885.94" "1" "1" "180")
(command "_insert" "blkuc5" "1600,886.68" "1" "1" "0")
(command "_insert" "blkuc5" "1600,886.31" "1" "1" "180")
(command "_insert" "blkuc5" "1600,887.05" "1" "1" "0")
(command "_insert" "blkuc5" "1600,886.68" "1" "1" "180")
(command "_insert" "blkuc5" "1600,887.42" "1" "1" "0")
(command "_insert" "blkuc5" "1600,887.05" "1" "1" "180")
(command "_insert" "blkuc5" "1600,887.79" "1" "1" "0")
(command "_insert" "blkuc5" "1600,887.42" "1" "1" "180")
(command "_insert" "blkuc5" "1600,888.16" "1" "1" "0")
(command "_insert" "blkuc5" "1600,887.79" "1" "1" "180")
(command "_insert" "blkuc5" "1600,888.53" "1" "1" "0")
(command "_insert" "blkuc5" "1600,888.16" "1" "1" "180")
(command "_insert" "blkuc5" "1600,888.9" "1" "1" "0")
(command "_insert" "blkuc5" "1600,888.53" "1" "1" "180")
(command "_insert" "blkuc5" "1600,889.27" "1" "1" "0")
(command "_insert" "blkuc5" "1600,888.9" "1" "1" "180")
(command "_insert" "blkuc5" "1600,889.64" "1" "1" "0")
(command "_insert" "blkuc5" "1600,889.27" "1" "1" "180")
(command "_insert" "blkuc5" "1600,890.01" "1" "1" "0")
(command "_insert" "blkuc5" "1600,889.64" "1" "1" "180")
(command "_insert" "blkuc5" "1600,890.38" "1" "1" "0")
(command "_insert" "blkuc5" "1600,890.01" "1" "1" "180")
(command "_insert" "blkuc5" "1600,890.75" "1" "1" "0")
(command "_insert" "blkuc5" "1600,890.38" "1" "1" "180")
(command "_insert" "blkuc5" "1600,891.12" "1" "1" "0")
(command "_insert" "blkuc5" "1600,890.75" "1" "1" "180")
(command "_insert" "blkuc5" "1600,891.49" "1" "1" "0")
(command "_insert" "blkuc5" "1600,891.12" "1" "1" "180")
(command "_insert" "blkuc5" "1600,891.86" "1" "1" "0")
(command "_insert" "blkuc5" "1600,891.49" "1" "1" "180")
(command "_insert" "blkuc5" "1600,892.23" "1" "1" "0")
(command "_insert" "blkuc5" "1600,891.86" "1" "1" "180")
(command "_insert" "blkuc5" "1600,892.6" "1" "1" "0")
(command "_insert" "blkuc5" "1600,892.23" "1" "1" "180")
(command "_insert" "blkuc5" "1600,892.97" "1" "1" "0")
(command "_insert" "blkuc5" "1600,892.6" "1" "1" "180")
(command "_insert" "blkuc5" "1600,893.34" "1" "1" "0")
(command "_insert" "blkuc5" "1600,892.97" "1" "1" "180")
(command "_insert" "blkuc5" "1600,893.71" "1" "1" "0")
(command "_insert" "blkuc5" "1600,893.34" "1" "1" "180")
(command "_insert" "blkuc5" "1600,894.08" "1" "1" "0")
(command "_insert" "blkuc5" "1600,893.71" "1" "1" "180")
(command "_insert" "blkuc5" "1600,894.45" "1" "1" "0")
(command "_insert" "blkuc5" "1600,894.08" "1" "1" "180")
(command "_insert" "blkuc5" "1600,894.82" "1" "1" "0")
(command "_insert" "blkuc5" "1600,894.45" "1" "1" "180")
(command "_insert" "blkuc5" "1600,895.19" "1" "1" "0")
(command "_insert" "blkuc5" "1600,894.82" "1" "1" "180")
(command "_insert" "blkuc5" "1600,895.56" "1" "1" "0")
(command "_insert" "blkuc5" "1600,895.19" "1" "1" "180")
(command "_insert" "blkuc5" "1600,895.93" "1" "1" "0")
(command "_insert" "blkuc5" "1600,895.56" "1" "1" "180")
(command "_insert" "blkuc5" "1600,896.3" "1" "1" "0")
(command "_insert" "blkuc5" "1600,895.93" "1" "1" "180")
(command "_insert" "blkuc5" "1600,896.67" "1" "1" "0")
(command "_insert" "blkuc5" "1600,896.3" "1" "1" "180")
(command "_insert" "blkuc5" "1600,897.04" "1" "1" "0")
(command "_insert" "blkuc5" "1600,896.67" "1" "1" "180")
(command "_insert" "blkuc5" "1600,897.41" "1" "1" "0")
(command "_insert" "blkuc5" "1600,897.04" "1" "1" "180")
(command "_insert" "blkuc5" "1600,897.78" "1" "1" "0")
(command "_insert" "blkuc5" "1600,897.41" "1" "1" "180")
(command "_insert" "blkuc5" "1600,898.15" "1" "1" "0")
(command "_insert" "blkuc5" "1600,897.78" "1" "1" "180")
(command "_insert" "blkuc5" "1600,898.52" "1" "1" "0")
(command "_insert" "blkuc5" "1600,898.15" "1" "1" "180")
(command "_insert" "blkuc5" "1600,898.89" "1" "1" "0")
(command "_insert" "blkuc5" "1600,898.52" "1" "1" "180")
(command "_insert" "blkuc5" "1600,899.26" "1" "1" "0")
(command "_insert" "blkuc5" "1600,898.89" "1" "1" "180")
(command "_insert" "blkuc5" "1600,899.63" "1" "1" "0")
(command "_insert" "blkuc5" "1600,899.26" "1" "1" "180")
(command "_insert" "blkuc5" "1600,900" "1" "1" "0")
(command "_insert" "blkuc5" "1600,899.63" "1" "1" "180")
(command "_insert" "blkuc5" "1600,900.37" "1" "1" "0")
(command "_insert" "blkuc5" "1600,900" "1" "1" "180")
(command "_insert" "blkuc5" "1600,900.74" "1" "1" "0")
(command "_insert" "blkuc5" "1600,900.37" "1" "1" "180")
(command "_insert" "blkuc5" "1600,901.11" "1" "1" "0")
(command "_insert" "blkuc5" "1600,900.74" "1" "1" "180")
(command "_insert" "blkuc5" "1600,901.48" "1" "1" "0")
(command "_insert" "blkuc5" "1600,901.11" "1" "1" "180")
(command "_insert" "blkuc5" "1600,901.85" "1" "1" "0")
(command "_insert" "blkuc5" "1600,901.48" "1" "1" "180")
(command "_insert" "blkuc5" "1600,902.22" "1" "1" "0")
(command "_insert" "blkuc5" "1600,901.85" "1" "1" "180")
(command "_insert" "blkuc5" "1600,902.59" "1" "1" "0")
(command "_insert" "blkuc5" "1600,902.22" "1" "1" "180")
(command "_insert" "blkuc5" "1600,902.96" "1" "1" "0")
(command "_insert" "blkuc5" "1600,902.59" "1" "1" "180")
(command "_insert" "blkuc5" "1600,903.33" "1" "1" "0")
(command "_insert" "blkuc5" "1600,902.96" "1" "1" "180")
(command "_insert" "blkuc5" "1600,903.7" "1" "1" "0")
(command "_insert" "blkuc5" "1600,903.33" "1" "1" "180")
(command "_insert" "blkuc5" "1600,904.07" "1" "1" "0")
(command "_insert" "blkuc5" "1600,903.7" "1" "1" "180")
(command "_insert" "blkuc5" "1600,904.44" "1" "1" "0")
(command "_insert" "blkuc5" "1600,904.07" "1" "1" "180")
(command "_insert" "blkuc5" "1600,904.81" "1" "1" "0")
(command "_insert" "blkuc5" "1600,904.44" "1" "1" "180")
(command "_insert" "blkuc5" "1600,905.18" "1" "1" "0")
(command "_insert" "blkuc5" "1600,904.81" "1" "1" "180")
(command "_insert" "blkuc5" "1600,905.55" "1" "1" "0")
(command "_insert" "blkuc5" "1600,905.18" "1" "1" "180")
(command "_insert" "blkuc5" "1600,905.92" "1" "1" "0")
(command "_insert" "blkuc5" "1600,905.55" "1" "1" "180")
(command "_insert" "blkuc5" "1600,906.29" "1" "1" "0")
(command "_insert" "blkuc5" "1600,905.92" "1" "1" "180")
(command "_insert" "blkuc5" "1600,906.66" "1" "1" "0")
(command "_insert" "blkuc5" "1600,906.29" "1" "1" "180")
(command "_insert" "blkuc5" "1600,907.03" "1" "1" "0")
(command "_insert" "blkuc5" "1600,906.66" "1" "1" "180")
(command "_insert" "blkuc5" "1600,907.4" "1" "1" "0")
(command "_insert" "blkuc5" "1600,907.03" "1" "1" "180")
(command "_insert" "blkuc5" "1600,907.77" "1" "1" "0")
(command "_insert" "blkuc5" "1600,907.4" "1" "1" "180")
(command "_insert" "blkuc5" "1600,908.14" "1" "1" "0")
(command "_insert" "blkuc5" "1600,907.77" "1" "1" "180")
(command "_insert" "blkuc5" "1600,908.51" "1" "1" "0")
(command "_insert" "blkuc5" "1600,908.14" "1" "1" "180")
(command "_insert" "blkuc5" "1600,908.88" "1" "1" "0")
(command "_insert" "blkuc5" "1600,908.51" "1" "1" "180")
(command "_insert" "blkuc5" "1600,909.25" "1" "1" "0")
(command "_insert" "blkuc5" "1600,908.88" "1" "1" "180")
(command "_insert" "blkuc5" "1600,909.62" "1" "1" "0")
(command "_insert" "blkuc5" "1600,909.25" "1" "1" "180")
(command "_insert" "blkuc5" "1600,909.99" "1" "1" "0")
(command "_insert" "blkuc5" "1600,909.62" "1" "1" "180")
(command "_insert" "blkuc5" "1600,910.36" "1" "1" "0")
(command "_insert" "blkuc5" "1600,909.99" "1" "1" "180")
(command "_insert" "blkuc5" "1600,910.73" "1" "1" "0")
(command "_insert" "blkuc5" "1600,910.36" "1" "1" "180")
(command "_insert" "blkuc5" "1600,911.1" "1" "1" "0")
(command "_insert" "blkuc5" "1600,910.73" "1" "1" "180")
(command "_insert" "blkuc5" "1600,911.47" "1" "1" "0")
(command "_insert" "blkuc5" "1600,911.1" "1" "1" "180")
(command "_insert" "blkuc5" "1600,911.84" "1" "1" "0")
(command "_insert" "blkuc5" "1600,911.47" "1" "1" "180")
(command "_insert" "blkuc5" "1600,912.21" "1" "1" "0")
(command "_insert" "blkuc5" "1600,911.84" "1" "1" "180")
(command "_insert" "blkuc5" "1600,912.58" "1" "1" "0")
(command "_insert" "blkuc5" "1600,912.21" "1" "1" "180")
(command "_insert" "blkuc5" "1600,912.95" "1" "1" "0")
(command "_insert" "blkuc5" "1600,912.58" "1" "1" "180")
(command "_insert" "blkuc5" "1600,913.32" "1" "1" "0")
(command "_insert" "blkuc5" "1600,912.95" "1" "1" "180")
(command "_insert" "blkuc5" "1600,913.69" "1" "1" "0")
(command "_insert" "blkuc5" "1600,913.32" "1" "1" "180")
(command "_insert" "blkuc5" "1600,914.06" "1" "1" "0")
(command "_insert" "blkuc5" "1600,913.69" "1" "1" "180")
(command "_insert" "blkuc5" "1600,914.43" "1" "1" "0")
(command "_insert" "blkuc5" "1600,914.06" "1" "1" "180")
(command "_insert" "blkuc5" "1600,914.8" "1" "1" "0")
(command "_insert" "blkuc5" "1600,914.43" "1" "1" "180")
(command "_insert" "blkuc5" "1600,915.17" "1" "1" "0")
(command "_insert" "blkuc5" "1600,914.8" "1" "1" "180")
(command "_insert" "blkuc5" "1600,915.54" "1" "1" "0")
(command "_insert" "blkuc5" "1600,915.17" "1" "1" "180")
(command "_insert" "blkuc5" "1600,915.91" "1" "1" "0")
(command "_insert" "blkuc5" "1600,915.54" "1" "1" "180")
(command "_insert" "blkuc5" "1600,916.28" "1" "1" "0")
(command "_insert" "blkuc5" "1600,915.91" "1" "1" "180")
(command "_insert" "blkuc5" "1600,916.65" "1" "1" "0")
(command "_insert" "blkuc5" "1600,916.28" "1" "1" "180")
(command "_insert" "blkuc5" "1600,917.02" "1" "1" "0")
(command "_insert" "blkuc5" "1600,916.65" "1" "1" "180")
(command "_insert" "blkuc5" "1600,917.39" "1" "1" "0")
(command "_insert" "blkuc5" "1600,917.02" "1" "1" "180")
(command "_insert" "blkuc5" "1600,917.76" "1" "1" "0")
(command "_insert" "blkuc5" "1600,917.39" "1" "1" "180")
(command "_insert" "blkuc5" "1600,918.13" "1" "1" "0")
(command "_insert" "blkuc5" "1600,917.76" "1" "1" "180")
(command "_insert" "blkuc5" "1600,918.5" "1" "1" "0")
(command "_insert" "blkuc5" "1600,918.13" "1" "1" "180")
(command "_insert" "blkuc5" "1600,918.87" "1" "1" "0")
(command "_insert" "blkuc5" "1600,918.5" "1" "1" "180")
(command "_insert" "blkuc5" "1600,919.24" "1" "1" "0")
(command "_insert" "blkuc5" "1600,918.87" "1" "1" "180")
(command "_insert" "blkuc5" "1600,919.61" "1" "1" "0")
(command "_insert" "blkuc5" "1600,919.24" "1" "1" "180")
(command "_insert" "blkuc5" "1600,919.98" "1" "1" "0")
(command "_insert" "blkuc5" "1600,919.61" "1" "1" "180")
(command "_insert" "blkuc5" "1600,920.35" "1" "1" "0")
(command "_insert" "blkuc5" "1600,919.98" "1" "1" "180")
(command "_insert" "blkuc5" "1600,920.72" "1" "1" "0")
(command "_insert" "blkuc5" "1600,920.35" "1" "1" "180")
(command "_insert" "blkuc5" "1600,921.09" "1" "1" "0")
(command "_insert" "blkuc5" "1600,920.72" "1" "1" "180")
(command "_insert" "blkuc5" "1600,921.46" "1" "1" "0")
(command "_insert" "blkuc5" "1600,921.09" "1" "1" "180")
(command "_insert" "blkuc5" "1600,921.83" "1" "1" "0")
(command "_insert" "blkuc5" "1600,921.46" "1" "1" "180")
(command "_insert" "blkuc5" "1600,922.2" "1" "1" "0")
(command "_insert" "blkuc5" "1600,921.83" "1" "1" "180")
(command "_insert" "blkuc5" "1600,922.57" "1" "1" "0")
(command "_insert" "blkuc5" "1600,922.2" "1" "1" "180")
(command "_insert" "blkuc5" "1600,922.94" "1" "1" "0")
(command "_insert" "blkuc5" "1600,922.57" "1" "1" "180")
(command "_insert" "blkuc5" "1600,923.31" "1" "1" "0")
(command "_insert" "blkuc5" "1600,922.94" "1" "1" "180")
(command "_insert" "blkuc5" "1600,923.68" "1" "1" "0")
(command "_insert" "blkuc5" "1600,923.31" "1" "1" "180")
(command "_insert" "blkuc5" "1600,924.05" "1" "1" "0")
(command "_insert" "blkuc5" "1600,923.68" "1" "1" "180")
(command "_insert" "blkuc5" "1600,924.42" "1" "1" "0")
(command "_insert" "blkuc5" "1600,924.05" "1" "1" "180")
(command "_insert" "blkuc5" "1600,924.79" "1" "1" "0")
(command "_insert" "blkuc5" "1600,924.42" "1" "1" "180")
(command "_insert" "blkuc5" "1600,925.16" "1" "1" "0")
(command "_insert" "blkuc5" "1600,924.79" "1" "1" "180")
(command "_insert" "blkuc5" "1600,925.53" "1" "1" "0")
(command "_insert" "blkuc5" "1600,925.16" "1" "1" "180")
(command "_insert" "blkuc5" "1600,925.9" "1" "1" "0")
(command "_insert" "blkuc5" "1600,925.53" "1" "1" "180")
(command "_insert" "blkuc5" "1600,926.27" "1" "1" "0")
(command "_insert" "blkuc5" "1600,925.9" "1" "1" "180")
(command "_insert" "blkuc5" "1600,926.64" "1" "1" "0")
(command "_insert" "blkuc5" "1600,926.27" "1" "1" "180")
(command "_insert" "blkuc5" "1600,927.01" "1" "1" "0")
(command "_insert" "blkuc5" "1600,926.64" "1" "1" "180")
(command "_insert" "blkuc5" "1600,927.38" "1" "1" "0")
(command "_insert" "blkuc5" "1600,927.01" "1" "1" "180")
(command "_insert" "blkuc5" "1600,927.75" "1" "1" "0")
(command "_insert" "blkuc5" "1600,927.38" "1" "1" "180")
(command "_layer" "set" "phccover" "")
(command "_rectangle" "1598.874,933.3" "1601.126,866.7")
(command "_layer" "set" "nitride" "")
(setq phc5 currobj)
(command "_layer" "set" "cover" "")
(command "_rectangle" "1598.874,836.7" "1601.126,963.3")
(command "_layer" "set" "nitride" "")
(command "_layer" "set" "text" "")
(command "_circle" "1597.924,846.7" "0.075")
(command "_circle" "1597.549,846.7" "0.15")
(command "_circle" "1597.174,846.7" "0.075")
(command "_circle" "1596.799,846.7" "0.15")
(command "_circle" "1597.924,848.7" "0.075")
(command "_circle" "1597.549,848.7" "0.075")
(command "_circle" "1597.174,848.7" "0.15")
(command "_circle" "1596.799,848.7" "0.15")
(command "_circle" "1597.924,850.7" "0.075")
(command "_circle" "1597.549,850.7" "0.15")
(command "_circle" "1597.174,850.7" "0.15")
(command "_circle" "1596.799,850.7" "0.15")
(command "_circle" "1597.924,852.7" "0.075")
(command "_circle" "1597.549,852.7" "0.075")
(command "_circle" "1597.174,852.7" "0.075")
(command "_circle" "1596.799,852.7" "0.075")
(command "_circle" "1596.424,852.7" "0.15")
(command "_circle" "1597.924,854.7" "0.075")
(command "_circle" "1597.549,854.7" "0.15")
(command "_circle" "1597.174,854.7" "0.075")
(command "_circle" "1596.799,854.7" "0.075")
(command "_circle" "1596.424,854.7" "0.15")
(command "_circle" "1597.924,856.7" "0.075")
(command "_circle" "1597.549,856.7" "0.075")
(command "_circle" "1597.174,856.7" "0.15")
(command "_circle" "1596.799,856.7" "0.075")
(command "_circle" "1596.424,856.7" "0.15")
(command "_circle" "1597.924,858.7" "0.075")
(command "_circle" "1597.549,858.7" "0.15")
(command "_circle" "1597.174,858.7" "0.15")
(command "_circle" "1596.799,858.7" "0.075")
(command "_circle" "1596.424,858.7" "0.15")
(command "_circle" "1597.924,860.7" "0.075")
(command "_circle" "1597.549,860.7" "0.075")
(command "_circle" "1597.174,860.7" "0.075")
(command "_circle" "1596.799,860.7" "0.15")
(command "_circle" "1596.424,860.7" "0.15")
(command "_circle" "1597.924,862.7" "0.075")
(command "_circle" "1597.549,862.7" "0.15")
(command "_circle" "1597.174,862.7" "0.075")
(command "_circle" "1596.799,862.7" "0.15")
(command "_circle" "1596.424,862.7" "0.15")
(command "_circle" "1597.924,864.7" "0.075")
(command "_circle" "1597.549,864.7" "0.075")
(command "_circle" "1597.174,864.7" "0.15")
(command "_circle" "1596.799,864.7" "0.15")
(command "_circle" "1596.424,864.7" "0.15")
(command "_circle" "1597.924,866.7" "0.075")
(command "_circle" "1597.549,866.7" "0.15")
(command "_circle" "1597.174,866.7" "0.15")
(command "_circle" "1596.799,866.7" "0.15")
(command "_circle" "1596.424,866.7" "0.15")
(command "_circle" "1597.924,868.7" "0.075")
(command "_circle" "1597.549,868.7" "0.075")
(command "_circle" "1597.174,868.7" "0.075")
(command "_circle" "1596.799,868.7" "0.075")
(command "_circle" "1596.424,868.7" "0.075")
(command "_circle" "1596.049,868.7" "0.15")
(command "_circle" "1597.924,870.7" "0.075")
(command "_circle" "1597.549,870.7" "0.15")
(command "_circle" "1597.174,870.7" "0.075")
(command "_circle" "1596.799,870.7" "0.075")
(command "_circle" "1596.424,870.7" "0.075")
(command "_circle" "1596.049,870.7" "0.15")
(command "_circle" "1597.924,872.7" "0.075")
(command "_circle" "1597.549,872.7" "0.075")
(command "_circle" "1597.174,872.7" "0.15")
(command "_circle" "1596.799,872.7" "0.075")
(command "_circle" "1596.424,872.7" "0.075")
(command "_circle" "1596.049,872.7" "0.15")
(command "_circle" "1597.924,874.7" "0.075")
(command "_circle" "1597.549,874.7" "0.15")
(command "_circle" "1597.174,874.7" "0.15")
(command "_circle" "1596.799,874.7" "0.075")
(command "_circle" "1596.424,874.7" "0.075")
(command "_circle" "1596.049,874.7" "0.15")
(command "_circle" "1597.924,876.7" "0.075")
(command "_circle" "1597.549,876.7" "0.075")
(command "_circle" "1597.174,876.7" "0.075")
(command "_circle" "1596.799,876.7" "0.15")
(command "_circle" "1596.424,876.7" "0.075")
(command "_circle" "1596.049,876.7" "0.15")
(command "_circle" "1597.924,878.7" "0.075")
(command "_circle" "1597.549,878.7" "0.15")
(command "_circle" "1597.174,878.7" "0.075")
(command "_circle" "1596.799,878.7" "0.15")
(command "_circle" "1596.424,878.7" "0.075")
(command "_circle" "1596.049,878.7" "0.15")
(command "_circle" "1597.924,880.7" "0.075")
(command "_circle" "1597.549,880.7" "0.075")
(command "_circle" "1597.174,880.7" "0.15")
(command "_circle" "1596.799,880.7" "0.15")
(command "_circle" "1596.424,880.7" "0.075")
(command "_circle" "1596.049,880.7" "0.15")
(command "_circle" "1597.924,882.7" "0.075")
(command "_circle" "1597.549,882.7" "0.15")
(command "_circle" "1597.174,882.7" "0.15")
(command "_circle" "1596.799,882.7" "0.15")
(command "_circle" "1596.424,882.7" "0.075")
(command "_circle" "1596.049,882.7" "0.15")
(command "_circle" "1597.924,884.7" "0.075")
(command "_circle" "1597.549,884.7" "0.075")
(command "_circle" "1597.174,884.7" "0.075")
(command "_circle" "1596.799,884.7" "0.075")
(command "_circle" "1596.424,884.7" "0.15")
(command "_circle" "1596.049,884.7" "0.15")
(command "_circle" "1597.924,886.7" "0.075")
(command "_circle" "1597.549,886.7" "0.15")
(command "_circle" "1597.174,886.7" "0.075")
(command "_circle" "1596.799,886.7" "0.075")
(command "_circle" "1596.424,886.7" "0.15")
(command "_circle" "1596.049,886.7" "0.15")
(command "_circle" "1597.924,888.7" "0.075")
(command "_circle" "1597.549,888.7" "0.075")
(command "_circle" "1597.174,888.7" "0.15")
(command "_circle" "1596.799,888.7" "0.075")
(command "_circle" "1596.424,888.7" "0.15")
(command "_circle" "1596.049,888.7" "0.15")
(command "_circle" "1597.924,890.7" "0.075")
(command "_circle" "1597.549,890.7" "0.15")
(command "_circle" "1597.174,890.7" "0.15")
(command "_circle" "1596.799,890.7" "0.075")
(command "_circle" "1596.424,890.7" "0.15")
(command "_circle" "1596.049,890.7" "0.15")
(command "_circle" "1597.924,892.7" "0.075")
(command "_circle" "1597.549,892.7" "0.075")
(command "_circle" "1597.174,892.7" "0.075")
(command "_circle" "1596.799,892.7" "0.15")
(command "_circle" "1596.424,892.7" "0.15")
(command "_circle" "1596.049,892.7" "0.15")
(command "_circle" "1597.924,894.7" "0.075")
(command "_circle" "1597.549,894.7" "0.15")
(command "_circle" "1597.174,894.7" "0.075")
(command "_circle" "1596.799,894.7" "0.15")
(command "_circle" "1596.424,894.7" "0.15")
(command "_circle" "1596.049,894.7" "0.15")
(command "_circle" "1597.924,896.7" "0.075")
(command "_circle" "1597.549,896.7" "0.075")
(command "_circle" "1597.174,896.7" "0.15")
(command "_circle" "1596.799,896.7" "0.15")
(command "_circle" "1596.424,896.7" "0.15")
(command "_circle" "1596.049,896.7" "0.15")
(command "_circle" "1597.924,898.7" "0.075")
(command "_circle" "1597.549,898.7" "0.15")
(command "_circle" "1597.174,898.7" "0.15")
(command "_circle" "1596.799,898.7" "0.15")
(command "_circle" "1596.424,898.7" "0.15")
(command "_circle" "1596.049,898.7" "0.15")
(command "_circle" "1597.924,900.7" "0.075")
(command "_circle" "1597.549,900.7" "0.075")
(command "_circle" "1597.174,900.7" "0.075")
(command "_circle" "1596.799,900.7" "0.075")
(command "_circle" "1596.424,900.7" "0.075")
(command "_circle" "1596.049,900.7" "0.075")
(command "_circle" "1595.674,900.7" "0.15")
(command "_circle" "1597.924,902.7" "0.075")
(command "_circle" "1597.549,902.7" "0.15")
(command "_circle" "1597.174,902.7" "0.075")
(command "_circle" "1596.799,902.7" "0.075")
(command "_circle" "1596.424,902.7" "0.075")
(command "_circle" "1596.049,902.7" "0.075")
(command "_circle" "1595.674,902.7" "0.15")
(command "_circle" "1597.924,904.7" "0.075")
(command "_circle" "1597.549,904.7" "0.075")
(command "_circle" "1597.174,904.7" "0.15")
(command "_circle" "1596.799,904.7" "0.075")
(command "_circle" "1596.424,904.7" "0.075")
(command "_circle" "1596.049,904.7" "0.075")
(command "_circle" "1595.674,904.7" "0.15")
(command "_circle" "1597.924,906.7" "0.075")
(command "_circle" "1597.549,906.7" "0.15")
(command "_circle" "1597.174,906.7" "0.15")
(command "_circle" "1596.799,906.7" "0.075")
(command "_circle" "1596.424,906.7" "0.075")
(command "_circle" "1596.049,906.7" "0.075")
(command "_circle" "1595.674,906.7" "0.15")
(command "_circle" "1597.924,908.7" "0.075")
(command "_circle" "1597.549,908.7" "0.075")
(command "_circle" "1597.174,908.7" "0.075")
(command "_circle" "1596.799,908.7" "0.15")
(command "_circle" "1596.424,908.7" "0.075")
(command "_circle" "1596.049,908.7" "0.075")
(command "_circle" "1595.674,908.7" "0.15")
(command "_circle" "1597.924,910.7" "0.075")
(command "_circle" "1597.549,910.7" "0.15")
(command "_circle" "1597.174,910.7" "0.075")
(command "_circle" "1596.799,910.7" "0.15")
(command "_circle" "1596.424,910.7" "0.075")
(command "_circle" "1596.049,910.7" "0.075")
(command "_circle" "1595.674,910.7" "0.15")
(command "_circle" "1597.924,912.7" "0.075")
(command "_circle" "1597.549,912.7" "0.075")
(command "_circle" "1597.174,912.7" "0.15")
(command "_circle" "1596.799,912.7" "0.15")
(command "_circle" "1596.424,912.7" "0.075")
(command "_circle" "1596.049,912.7" "0.075")
(command "_circle" "1595.674,912.7" "0.15")
(command "_circle" "1597.924,914.7" "0.075")
(command "_circle" "1597.549,914.7" "0.15")
(command "_circle" "1597.174,914.7" "0.15")
(command "_circle" "1596.799,914.7" "0.15")
(command "_circle" "1596.424,914.7" "0.075")
(command "_circle" "1596.049,914.7" "0.075")
(command "_circle" "1595.674,914.7" "0.15")
(command "_circle" "1597.924,916.7" "0.075")
(command "_circle" "1597.549,916.7" "0.075")
(command "_circle" "1597.174,916.7" "0.075")
(command "_circle" "1596.799,916.7" "0.075")
(command "_circle" "1596.424,916.7" "0.15")
(command "_circle" "1596.049,916.7" "0.075")
(command "_circle" "1595.674,916.7" "0.15")
(command "_circle" "1597.924,918.7" "0.075")
(command "_circle" "1597.549,918.7" "0.15")
(command "_circle" "1597.174,918.7" "0.075")
(command "_circle" "1596.799,918.7" "0.075")
(command "_circle" "1596.424,918.7" "0.15")
(command "_circle" "1596.049,918.7" "0.075")
(command "_circle" "1595.674,918.7" "0.15")
(command "_circle" "1597.924,920.7" "0.075")
(command "_circle" "1597.549,920.7" "0.075")
(command "_circle" "1597.174,920.7" "0.15")
(command "_circle" "1596.799,920.7" "0.075")
(command "_circle" "1596.424,920.7" "0.15")
(command "_circle" "1596.049,920.7" "0.075")
(command "_circle" "1595.674,920.7" "0.15")
(command "_circle" "1597.924,922.7" "0.075")
(command "_circle" "1597.549,922.7" "0.15")
(command "_circle" "1597.174,922.7" "0.15")
(command "_circle" "1596.799,922.7" "0.075")
(command "_circle" "1596.424,922.7" "0.15")
(command "_circle" "1596.049,922.7" "0.075")
(command "_circle" "1595.674,922.7" "0.15")
(command "_circle" "1597.924,924.7" "0.075")
(command "_circle" "1597.549,924.7" "0.075")
(command "_circle" "1597.174,924.7" "0.075")
(command "_circle" "1596.799,924.7" "0.15")
(command "_circle" "1596.424,924.7" "0.15")
(command "_circle" "1596.049,924.7" "0.075")
(command "_circle" "1595.674,924.7" "0.15")
(command "_circle" "1597.924,926.7" "0.075")
(command "_circle" "1597.549,926.7" "0.15")
(command "_circle" "1597.174,926.7" "0.075")
(command "_circle" "1596.799,926.7" "0.15")
(command "_circle" "1596.424,926.7" "0.15")
(command "_circle" "1596.049,926.7" "0.075")
(command "_circle" "1595.674,926.7" "0.15")
(command "_circle" "1597.924,928.7" "0.075")
(command "_circle" "1597.549,928.7" "0.075")
(command "_circle" "1597.174,928.7" "0.15")
(command "_circle" "1596.799,928.7" "0.15")
(command "_circle" "1596.424,928.7" "0.15")
(command "_circle" "1596.049,928.7" "0.075")
(command "_circle" "1595.674,928.7" "0.15")
(command "_circle" "1597.924,930.7" "0.075")
(command "_circle" "1597.549,930.7" "0.15")
(command "_circle" "1597.174,930.7" "0.15")
(command "_circle" "1596.799,930.7" "0.15")
(command "_circle" "1596.424,930.7" "0.15")
(command "_circle" "1596.049,930.7" "0.075")
(command "_circle" "1595.674,930.7" "0.15")
(command "_circle" "1597.924,932.7" "0.075")
(command "_circle" "1597.549,932.7" "0.075")
(command "_circle" "1597.174,932.7" "0.075")
(command "_circle" "1596.799,932.7" "0.075")
(command "_circle" "1596.424,932.7" "0.075")
(command "_circle" "1596.049,932.7" "0.15")
(command "_circle" "1595.674,932.7" "0.15")
(command "_circle" "1597.924,934.7" "0.075")
(command "_circle" "1597.549,934.7" "0.15")
(command "_circle" "1597.174,934.7" "0.075")
(command "_circle" "1596.799,934.7" "0.075")
(command "_circle" "1596.424,934.7" "0.075")
(command "_circle" "1596.049,934.7" "0.15")
(command "_circle" "1595.674,934.7" "0.15")
(command "_circle" "1597.924,936.7" "0.075")
(command "_circle" "1597.549,936.7" "0.075")
(command "_circle" "1597.174,936.7" "0.15")
(command "_circle" "1596.799,936.7" "0.075")
(command "_circle" "1596.424,936.7" "0.075")
(command "_circle" "1596.049,936.7" "0.15")
(command "_circle" "1595.674,936.7" "0.15")
(command "_circle" "1597.924,938.7" "0.075")
(command "_circle" "1597.549,938.7" "0.15")
(command "_circle" "1597.174,938.7" "0.15")
(command "_circle" "1596.799,938.7" "0.075")
(command "_circle" "1596.424,938.7" "0.075")
(command "_circle" "1596.049,938.7" "0.15")
(command "_circle" "1595.674,938.7" "0.15")
(command "_circle" "1597.924,940.7" "0.075")
(command "_circle" "1597.549,940.7" "0.075")
(command "_circle" "1597.174,940.7" "0.075")
(command "_circle" "1596.799,940.7" "0.15")
(command "_circle" "1596.424,940.7" "0.075")
(command "_circle" "1596.049,940.7" "0.15")
(command "_circle" "1595.674,940.7" "0.15")
(command "_circle" "1597.924,942.7" "0.075")
(command "_circle" "1597.549,942.7" "0.15")
(command "_circle" "1597.174,942.7" "0.075")
(command "_circle" "1596.799,942.7" "0.15")
(command "_circle" "1596.424,942.7" "0.075")
(command "_circle" "1596.049,942.7" "0.15")
(command "_circle" "1595.674,942.7" "0.15")
(command "_circle" "1597.924,944.7" "0.075")
(command "_circle" "1597.549,944.7" "0.075")
(command "_circle" "1597.174,944.7" "0.15")
(command "_circle" "1596.799,944.7" "0.15")
(command "_circle" "1596.424,944.7" "0.075")
(command "_circle" "1596.049,944.7" "0.15")
(command "_circle" "1595.674,944.7" "0.15")
(command "_circle" "1597.924,946.7" "0.075")
(command "_circle" "1597.549,946.7" "0.15")
(command "_circle" "1597.174,946.7" "0.15")
(command "_circle" "1596.799,946.7" "0.15")
(command "_circle" "1596.424,946.7" "0.075")
(command "_circle" "1596.049,946.7" "0.15")
(command "_circle" "1595.674,946.7" "0.15")
(command "_circle" "1597.924,948.7" "0.075")
(command "_circle" "1597.549,948.7" "0.075")
(command "_circle" "1597.174,948.7" "0.075")
(command "_circle" "1596.799,948.7" "0.075")
(command "_circle" "1596.424,948.7" "0.15")
(command "_circle" "1596.049,948.7" "0.15")
(command "_circle" "1595.674,948.7" "0.15")
(command "_circle" "1597.924,950.7" "0.075")
(command "_circle" "1597.549,950.7" "0.15")
(command "_circle" "1597.174,950.7" "0.075")
(command "_circle" "1596.799,950.7" "0.075")
(command "_circle" "1596.424,950.7" "0.15")
(command "_circle" "1596.049,950.7" "0.15")
(command "_circle" "1595.674,950.7" "0.15")
(command "_circle" "1597.924,952.7" "0.075")
(command "_circle" "1597.549,952.7" "0.075")
(command "_circle" "1597.174,952.7" "0.15")
(command "_circle" "1596.799,952.7" "0.075")
(command "_circle" "1596.424,952.7" "0.15")
(command "_circle" "1596.049,952.7" "0.15")
(command "_circle" "1595.674,952.7" "0.15")
(command "_circle" "1597.924,954.7" "0.075")
(command "_circle" "1597.549,954.7" "0.15")
(command "_circle" "1597.174,954.7" "0.15")
(command "_circle" "1596.799,954.7" "0.075")
(command "_circle" "1596.424,954.7" "0.15")
(command "_circle" "1596.049,954.7" "0.15")
(command "_circle" "1595.674,954.7" "0.15")
(command "_circle" "1597.924,956.7" "0.075")
(command "_circle" "1597.549,956.7" "0.075")
(command "_circle" "1597.174,956.7" "0.075")
(command "_circle" "1596.799,956.7" "0.15")
(command "_circle" "1596.424,956.7" "0.15")
(command "_circle" "1596.049,956.7" "0.15")
(command "_circle" "1595.674,956.7" "0.15")
(command "_circle" "1597.924,958.7" "0.075")
(command "_circle" "1597.549,958.7" "0.15")
(command "_circle" "1597.174,958.7" "0.075")
(command "_circle" "1596.799,958.7" "0.15")
(command "_circle" "1596.424,958.7" "0.15")
(command "_circle" "1596.049,958.7" "0.15")
(command "_circle" "1595.674,958.7" "0.15")
(command "_circle" "1597.924,960.7" "0.075")
(command "_circle" "1597.549,960.7" "0.075")
(command "_circle" "1597.174,960.7" "0.15")
(command "_circle" "1596.799,960.7" "0.15")
(command "_circle" "1596.424,960.7" "0.15")
(command "_circle" "1596.049,960.7" "0.15")
(command "_circle" "1595.674,960.7" "0.15")
(command "_circle" "1597.924,962.7" "0.075")
(command "_circle" "1597.549,962.7" "0.15")
(command "_circle" "1597.174,962.7" "0.15")
(command "_circle" "1596.799,962.7" "0.15")
(command "_circle" "1596.424,962.7" "0.15")
(command "_circle" "1596.049,962.7" "0.15")
(command "_circle" "1595.674,962.7" "0.15")
(command "_layer" "set" "nitride" "")
(command "_layer" "set" "text" "")
(command-s "_text" "1586.874,963.3" "2" "-90" "a = 370 nm" )
(sssetfirst nil (ssget "_L"))
(if (not (numberp (vl-string-search "Mac" (getvar "platform")))) (c:txtexp))
(command "_layer" "set" "nitride" "")
(command "_layer" "set" "text" "")
(command-s "_text" "1583.874,963.3" "2" "-90" "gap = 270 nm" )
(sssetfirst nil (ssget "_L"))
(if (not (numberp (vl-string-search "Mac" (getvar "platform")))) (c:txtexp))
(command "_layer" "set" "nitride" "")
(command "_layer" "set" "text" "")
(command-s "_text" "1580.874,963.3" "2" "-90" "amplitude = 134 nm" )
(sssetfirst nil (ssget "_L"))
(if (not (numberp (vl-string-search "Mac" (getvar "platform")))) (c:txtexp))
(command "_layer" "set" "nitride" "")
(command "_layer" "set" "text" "")
(command-s "_text" "1577.874,963.3" "2" "-90" "start width = 280 nm" )
(sssetfirst nil (ssget "_L"))
(if (not (numberp (vl-string-search "Mac" (getvar "platform")))) (c:txtexp))
(command "_layer" "set" "nitride" "")
(command "_layer" "set" "text" "")
(command-s "_text" "1574.874,963.3" "2" "-90" "width = 294 nm" )
(sssetfirst nil (ssget "_L"))
(if (not (numberp (vl-string-search "Mac" (getvar "platform")))) (c:txtexp))
(command "_layer" "set" "nitride" "")
(command "_layer" "set" "text" "")
(command-s "_text" "1571.874,963.3" "2" "-90" "taper: 15" )
(sssetfirst nil (ssget "_L"))
(if (not (numberp (vl-string-search "Mac" (getvar "platform")))) (c:txtexp))
(command "_layer" "set" "nitride" "")
(command "_layer" "set" "text" "")
(command-s "_text" "1568.874,963.3" "2" "-90" "nominal: 150" )
(sssetfirst nil (ssget "_L"))
(if (not (numberp (vl-string-search "Mac" (getvar "platform")))) (c:txtexp))
(command "_layer" "set" "nitride" "")
(command "_layer" "set" "indicators" "")
(setq coords (list 
(list 1520.415 940) 
(list 1520.415 920) 
(list 1500.415 900) 
(list 1520.415 880) 
(list 1520.415 860) 
(list 1520.415 900) 
(list 1520.415 887.0711) 
(list 1507.4861 900) 
(list 1520.415 912.9289) 
(list 1520.415 900)))
(apply 'command (append '("pline") coords '("c")))
(command "._fillet" "radius" "1" "._fillet" "P" (entlast))
(setq coords (list 
(list 1679.585 940) 
(list 1679.585 920) 
(list 1699.585 900) 
(list 1679.585 880) 
(list 1679.585 860) 
(list 1679.585 900) 
(list 1679.585 887.0711) 
(list 1692.5139 900) 
(list 1679.585 912.9289) 
(list 1679.585 900)))
(apply 'command (append '("pline") coords '("c")))
(command "._fillet" "radius" "1" "._fillet" "P" (entlast))
(command "_layer" "set" "holes" "")
(command "_circle" "1518.0629,914.1124" "0.5")
(command "_circle" "1515.7109,911.7603" "0.5")
(command "_circle" "1513.3588,909.4083" "0.5")
(command "_circle" "1511.0067,907.0562" "0.5")
(command "_circle" "1508.6547,904.7041" "0.5")
(command "_circle" "1506.3026,902.3521" "0.5")
(command "_circle" "1503.9505,900" "0.5")
(command "_circle" "1506.3026,897.6479" "0.5")
(command "_circle" "1508.6547,895.2959" "0.5")
(command "_circle" "1511.0067,892.9438" "0.5")
(command "_circle" "1513.3588,890.5917" "0.5")
(command "_circle" "1515.7109,888.2397" "0.5")
(command "_circle" "1518.0629,885.8876" "0.5")
(command "_circle" "1681.9371,914.1124" "0.5")
(command "_circle" "1684.2891,911.7603" "0.5")
(command "_circle" "1686.6412,909.4083" "0.5")
(command "_circle" "1688.9933,907.0562" "0.5")
(command "_circle" "1691.3453,904.7041" "0.5")
(command "_circle" "1693.6974,902.3521" "0.5")
(command "_circle" "1696.0495,900" "0.5")
(command "_circle" "1693.6974,897.6479" "0.5")
(command "_circle" "1691.3453,895.2959" "0.5")
(command "_circle" "1688.9933,892.9438" "0.5")
(command "_circle" "1686.6412,890.5917" "0.5")
(command "_circle" "1684.2891,888.2397" "0.5")
(command "_circle" "1681.9371,885.8876" "0.5")
(command "_layer" "set" "nitride" "")
(command "_block" "blkcoupler5" "1600,900" coupler5 "")
(command "_insert" "blkcoupler5" "1600,900" "1" "1" "0")
(command "_insert" "blkcoupler5" "1600,900" "1" "1" "180")
(command "_block" "blksinglenanobeam5" "1600,900" singlenanobeam5 "")
(command "_insert" "blksinglenanobeam5" "1600,900" "1" "1" "0")
(command "_insert" "blksinglenanobeam5" "1600,900" "1" "1" "180")
(command "_block" "blkanglednodearray5" "1600,900" anglednodearray5 "")
(command "_insert" "blkanglednodearray5" "1600,900" "1" "1" "0")
(command "_insert" "blkanglednodearray5" "1600,900" "1" "1" "180")
(command "_block" "blkcooledsinglenanobeam5" "1600,900" cooledsinglenanobeam5 "")
(command "_insert" "blkcooledsinglenanobeam5" "1600,900" "1" "1" "0")
(command "_insert" "blkcooledsinglenanobeam5" "1600,900" "1" "1" "180")
(command "_block" "blkyjunction5" "1600,900" yjunction5 "")
(command "_insert" "blkyjunction5" "1600,900" "1" "1" "0")
(command "_insert" "blkyjunction5" "1600,900" "1" "1" "180")
; DRAWING BULGING VEE GROOVE
(command "_layer" "set" "vgroove" "")
(setq coords (list 
(list 1525.415 -605) 
(list 1525.415 0) 
(list 1525.415 0) 
(list 1525.415 1800) 
(list 1525.415 1800) 
(list 1525.415 2405) 
(list 1674.585 2405) 
(list 1674.585 1800) 
(list 1674.585 1800) 
(list 1674.585 0) 
(list 1674.585 0) 
(list 1674.585 -605)))
(apply 'command (append '("pline") coords '("c")))
(command "._fillet" "radius" "0" "._fillet" "P" (entlast))
(command "_layer" "set" "window" "")
(command "_rectangle" "1525.415,-1935" "1674.585,-600")
(command "_rectangle" "1525.415,2400" "1674.585,5300")
(command "_layer" "set" "grid" "")
(command "_rectangle" "1526.415,-1934" "1549.9433,-1909.2133")
(command "_array" "last" "" "R" "75" "3" "25.7867" "24.5283")
(command "_rectangle" "1601,-1934" "1624.5283,-1909.2133")
(command "_array" "last" "" "R" "75" "3" "25.7867" "24.5283")
(command "_rectangle" "1526.415,1" "1549.9433,25.7")
(command "_array" "last" "" "R" "70" "3" "25.7" "24.5283")
(command "_rectangle" "1601,1" "1624.5283,25.7")
(command "_array" "last" "" "R" "70" "3" "25.7" "24.5283")
(command "_rectangle" "1526.415,1801" "1549.9433,1825.9185")
(command "_array" "last" "" "R" "135" "3" "25.9185" "24.5283")
(command "_rectangle" "1601,1801" "1624.5283,1825.9185")
(command "_array" "last" "" "R" "135" "3" "25.9185" "24.5283")
(command "_layer" "set" "vgrooveFDA" "")
(command "_rectangle" "1674.585,-2233" "1525.415,-1933")
(command "_layer" "set" "nitride" "")
(command "_layer" "set" "holes" "")
(command "_circle" "1677.085,331.5" "0.5")
(command "_array" "last" "" "R" "379" "1" "3" "2.5")
(command "_circle" "1522.915,331.5" "0.5")
(command "_array" "last" "" "R" "379" "1" "3" "-2.5")
(command "_layer" "set" "nitride" "")
(command "_layer" "set" "window" "")
(command "_layer" "set" "window" "")
(command "_rectangle" "1679.585,0" "1840.415,1800")
(command "._fillet" "radius" "20" "._fillet" "P" (entlast))
(command "_layer" "set" "grid" "")
(command "_rectangle" "1680.585,1" "1702.4179,25.7")
(command "_array" "last" "" "R" "70" "7" "25.7" "22.8329")
(command "_layer" "set" "nitride" "")
; DRAWING REGION LAYER
(command "_layer" "set" "regionLayer5" "")
(command "_rectangle" "1520,-460" "1680,2260")
(command "_layer" "set" "nitride" "")
(setq coupler5 nil)
(setq singlenanobeam5 nil)
(setq anglednodearray5 nil)
(setq cooledsinglenanobeam5 nil)
(setq yjunction5 nil)
; DEVICE #6
(command "_layer" "set" "window" "")
(command "_circle" "1832.915,-415" "5")
(command "_circle" "1832.915,-402.5" "5")
(command "_circle" "1832.915,-390" "5")
(command "_circle" "1832.915,-377.5" "5")
(command "_circle" "1820.415,-415" "5")
(command "_circle" "1820.415,-402.5" "5")
(command "_layer" "set" "nitride" "")
(setq currobj nil)
(setq currobj (ssadd))
; DRAWING COUPLER
(setq coords (list 
(list 1920.0645 -415) 
(list 1920.0645 -413) 
(list 1993.585 -413) 
(list 1993.585 -413) 
(list 1993.9677 -413.0761) 
(list 1994.2921 -413.2929) 
(list 1994.5089 -413.6173) 
(list 1994.585 -414) 
(list 1994.585 -411.8) 
(list 1994.585 -411.8) 
(list 1994.5089 -412.1827) 
(list 1994.2921 -412.5071) 
(list 1993.9677 -412.7239) 
(list 1993.585 -412.8) 
(list 1920.0645 -412.8) 
(list 1920.0645 -410.8) 
(list 1919.9355 -410.8) 
(list 1919.9355 -412.8) 
(list 1846.415 -412.8) 
(list 1846.0323 -412.7239) 
(list 1845.7079 -412.5071) 
(list 1845.4911 -412.1827) 
(list 1845.415 -411.8) 
(list 1845.415 -411.8) 
(list 1845.415 -414) 
(list 1845.4911 -413.6173) 
(list 1845.7079 -413.2929) 
(list 1846.0323 -413.0761) 
(list 1846.415 -413) 
(list 1846.415 -413) 
(list 1919.9355 -413) 
(list 1919.9355 -415)))
(apply 'command (append '("pline") coords '("c")))
(setq currobj (ssadd (entlast) currobj))
(command "._fillet" "radius" "0.3" "._fillet" "P" (entlast))
(command "_layer" "set" "holes" "")
(command "_circle" "1920,-412.9" "0.113")
(setq currobj (ssadd (entlast) currobj))
(command "_layer" "set" "nitride" "")
(command "_layer" "set" "text" "")
(command "_circle" "1919.2,-415" "0.075")
(command "_circle" "1919.2,-414.7" "0.075")
(command "_circle" "1919.2,-414.4" "0.075")
(command "_circle" "1918.9,-415" "0.075")
(command "_circle" "1918.9,-414.7" "0.075")
(command "_circle" "1918.9,-414.4" "0.075")
(command "_circle" "1918.6,-415" "0.075")
(command "_circle" "1918.6,-414.7" "0.075")
(command "_circle" "1918.6,-414.4" "0.075")
(command "_layer" "set" "nitride" "")
(command "_layer" "set" "prebias" "")
(command "_rectangle" "1845.415,-414" "1994.585,-411.8")
(setq currobj (ssadd (entlast) currobj))
(command "_rectangle" "1919.9355,-415" "1920.0645,-410.8")
(setq currobj (ssadd (entlast) currobj))
(command "_layer" "set" "nitride" "")
(setq coupler6 currobj)
(setq currobj nil)
(setq currobj (ssadd))
; DRAWING SINGLE NANOBEAM
(setq coords (list 
(list 1920.0645 -410.8) 
(list 1920.0645 -409.1417) 
(list 1920.0645 -407.4833) 
(list 1920.0645 -405.825) 
(list 1920.0645 -404.1667) 
(list 1920.0645 -402.5083) 
(list 1920.0645 -400.85) 
(list 1920.0645 -399.1917) 
(list 1920.0645 -397.5333) 
(list 1920.0646 -395.875) 
(list 1920.0646 -394.2167) 
(list 1920.0646 -392.5583) 
(list 1920.0646 -390.9) 
(list 1920.0647 -389.2417) 
(list 1920.0647 -387.5833) 
(list 1920.0647 -385.925) 
(list 1920.0648 -384.2667) 
(list 1920.0648 -382.6083) 
(list 1920.0649 -380.95) 
(list 1920.065 -379.2917) 
(list 1920.0651 -377.6333) 
(list 1920.0651 -375.975) 
(list 1920.0652 -374.3167) 
(list 1920.0653 -372.6583) 
(list 1920.0655 -371) 
(list 1920.0656 -369.3417) 
(list 1920.0657 -367.6833) 
(list 1920.0659 -366.025) 
(list 1920.066 -364.3667) 
(list 1920.0662 -362.7083) 
(list 1920.0664 -361.05) 
(list 1920.0666 -359.3917) 
(list 1920.0668 -357.7333) 
(list 1920.067 -356.075) 
(list 1920.0672 -354.4167) 
(list 1920.0675 -352.7583) 
(list 1920.0678 -351.1) 
(list 1920.068 -349.4417) 
(list 1920.0683 -347.7833) 
(list 1920.0686 -346.125) 
(list 1920.069 -344.4667) 
(list 1920.0693 -342.8083) 
(list 1920.0697 -341.15) 
(list 1920.07 -339.4917) 
(list 1920.0704 -337.8333) 
(list 1920.0709 -336.175) 
(list 1920.0713 -334.5167) 
(list 1920.0717 -332.8583) 
(list 1920.0722 -331.2) 
(list 1920.0727 -329.5417) 
(list 1920.0732 -327.8833) 
(list 1920.0738 -326.225) 
(list 1920.0743 -324.5667) 
(list 1920.0749 -322.9083) 
(list 1920.0755 -321.25) 
(list 1920.0761 -319.5917) 
(list 1920.0767 -317.9333) 
(list 1920.0774 -316.275) 
(list 1920.0781 -314.6167) 
(list 1920.0788 -312.9583) 
(list 1920.0796 -311.3) 
(list 1920.0803 -309.6417) 
(list 1920.0811 -307.9833) 
(list 1920.0819 -306.325) 
(list 1920.0828 -304.6667) 
(list 1920.0837 -303.0083) 
(list 1920.0845 -301.35) 
(list 1920.0855 -299.6917) 
(list 1920.0864 -298.0333) 
(list 1920.0874 -296.375) 
(list 1920.0884 -294.7167) 
(list 1920.0895 -293.0583) 
(list 1920.0905 -291.4) 
(list 1920.0916 -289.7417) 
(list 1920.0928 -288.0833) 
(list 1920.0939 -286.425) 
(list 1920.0951 -284.7667) 
(list 1920.0963 -283.1083) 
(list 1920.0976 -281.45) 
(list 1920.0989 -279.7917) 
(list 1920.1002 -278.1333) 
(list 1920.1016 -276.475) 
(list 1920.1029 -274.8167) 
(list 1920.1044 -273.1583) 
(list 1920.1058 -271.5) 
(list 1920.1073 -269.8417) 
(list 1920.1089 -268.1833) 
(list 1920.1104 -266.525) 
(list 1920.112 -264.8667) 
(list 1920.1137 -263.2083) 
(list 1920.1153 -261.55) 
(list 1920.117 -259.8917) 
(list 1920.1188 -258.2333) 
(list 1920.1206 -256.575) 
(list 1920.1224 -254.9167) 
(list 1920.1243 -253.2583) 
(list 1920.1262 -251.6) 
(list 1920.1281 -249.9417) 
(list 1920.1301 -248.2833) 
(list 1920.1322 -246.625) 
(list 1920.1342 -244.9667) 
(list 1920.1363 -243.3083) 
(list 1920.1385 -241.65) 
(list 1920.1407 -239.9917) 
(list 1920.1429 -238.3333) 
(list 1920.1452 -236.675) 
(list 1920.1476 -235.0167) 
(list 1920.1499 -233.3583) 
(list 1920.1523 -231.7) 
(list 1920.1548 -230.0417) 
(list 1920.1573 -228.3833) 
(list 1920.1599 -226.725) 
(list 1920.1625 -225.0667) 
(list 1920.1651 -223.4083) 
(list 1920.1678 -221.75) 
(list 1920.1706 -220.0917) 
(list 1920.1733 -218.4333) 
(list 1920.1762 -216.775) 
(list 1920.1791 -215.1167) 
(list 1920.182 -213.4583) 
(list 1920.185 -211.8) 
(list 1919.815 -211.8) 
(list 1919.818 -213.4583) 
(list 1919.8209 -215.1167) 
(list 1919.8238 -216.775) 
(list 1919.8267 -218.4333) 
(list 1919.8294 -220.0917) 
(list 1919.8322 -221.75) 
(list 1919.8349 -223.4083) 
(list 1919.8375 -225.0667) 
(list 1919.8401 -226.725) 
(list 1919.8427 -228.3833) 
(list 1919.8452 -230.0417) 
(list 1919.8477 -231.7) 
(list 1919.8501 -233.3583) 
(list 1919.8524 -235.0167) 
(list 1919.8548 -236.675) 
(list 1919.8571 -238.3333) 
(list 1919.8593 -239.9917) 
(list 1919.8615 -241.65) 
(list 1919.8637 -243.3083) 
(list 1919.8658 -244.9667) 
(list 1919.8678 -246.625) 
(list 1919.8699 -248.2833) 
(list 1919.8719 -249.9417) 
(list 1919.8738 -251.6) 
(list 1919.8757 -253.2583) 
(list 1919.8776 -254.9167) 
(list 1919.8794 -256.575) 
(list 1919.8812 -258.2333) 
(list 1919.883 -259.8917) 
(list 1919.8847 -261.55) 
(list 1919.8863 -263.2083) 
(list 1919.888 -264.8667) 
(list 1919.8896 -266.525) 
(list 1919.8911 -268.1833) 
(list 1919.8927 -269.8417) 
(list 1919.8942 -271.5) 
(list 1919.8956 -273.1583) 
(list 1919.8971 -274.8167) 
(list 1919.8984 -276.475) 
(list 1919.8998 -278.1333) 
(list 1919.9011 -279.7917) 
(list 1919.9024 -281.45) 
(list 1919.9037 -283.1083) 
(list 1919.9049 -284.7667) 
(list 1919.9061 -286.425) 
(list 1919.9072 -288.0833) 
(list 1919.9084 -289.7417) 
(list 1919.9095 -291.4) 
(list 1919.9105 -293.0583) 
(list 1919.9116 -294.7167) 
(list 1919.9126 -296.375) 
(list 1919.9136 -298.0333) 
(list 1919.9145 -299.6917) 
(list 1919.9155 -301.35) 
(list 1919.9163 -303.0083) 
(list 1919.9172 -304.6667) 
(list 1919.9181 -306.325) 
(list 1919.9189 -307.9833) 
(list 1919.9197 -309.6417) 
(list 1919.9204 -311.3) 
(list 1919.9212 -312.9583) 
(list 1919.9219 -314.6167) 
(list 1919.9226 -316.275) 
(list 1919.9233 -317.9333) 
(list 1919.9239 -319.5917) 
(list 1919.9245 -321.25) 
(list 1919.9251 -322.9083) 
(list 1919.9257 -324.5667) 
(list 1919.9262 -326.225) 
(list 1919.9268 -327.8833) 
(list 1919.9273 -329.5417) 
(list 1919.9278 -331.2) 
(list 1919.9283 -332.8583) 
(list 1919.9287 -334.5167) 
(list 1919.9291 -336.175) 
(list 1919.9296 -337.8333) 
(list 1919.93 -339.4917) 
(list 1919.9303 -341.15) 
(list 1919.9307 -342.8083) 
(list 1919.931 -344.4667) 
(list 1919.9314 -346.125) 
(list 1919.9317 -347.7833) 
(list 1919.932 -349.4417) 
(list 1919.9322 -351.1) 
(list 1919.9325 -352.7583) 
(list 1919.9328 -354.4167) 
(list 1919.933 -356.075) 
(list 1919.9332 -357.7333) 
(list 1919.9334 -359.3917) 
(list 1919.9336 -361.05) 
(list 1919.9338 -362.7083) 
(list 1919.934 -364.3667) 
(list 1919.9341 -366.025) 
(list 1919.9343 -367.6833) 
(list 1919.9344 -369.3417) 
(list 1919.9345 -371) 
(list 1919.9347 -372.6583) 
(list 1919.9348 -374.3167) 
(list 1919.9349 -375.975) 
(list 1919.9349 -377.6333) 
(list 1919.935 -379.2917) 
(list 1919.9351 -380.95) 
(list 1919.9352 -382.6083) 
(list 1919.9352 -384.2667) 
(list 1919.9353 -385.925) 
(list 1919.9353 -387.5833) 
(list 1919.9353 -389.2417) 
(list 1919.9354 -390.9) 
(list 1919.9354 -392.5583) 
(list 1919.9354 -394.2167) 
(list 1919.9354 -395.875) 
(list 1919.9355 -397.5333) 
(list 1919.9355 -399.1917) 
(list 1919.9355 -400.85) 
(list 1919.9355 -402.5083) 
(list 1919.9355 -404.1667) 
(list 1919.9355 -405.825) 
(list 1919.9355 -407.4833) 
(list 1919.9355 -409.1417) 
(list 1919.9355 -410.8)))
(apply 'command (append '("pline") coords '("c")))
(setq currobj (ssadd (entlast) currobj))
(command "_layer" "set" "prebias" "")
(command "_rectangle" "1919.815,-410.8" "1920.185,-211.8")
(setq currobj (ssadd (entlast) currobj))
(command "_layer" "set" "nitride" "")
(setq singlenanobeam6 currobj)
(setq currobj nil)
(setq currobj (ssadd))
; DRAWING NODE ARRAY
(setq coords (list 
(list 1920.185 -211.8) 
(list 1920.5625 -201.8) 
(list 1920.5625 -201.8) 
(list 1920.5625 -200.8) 
(list 1994.585 -212.6864) 
(list 1994.585 -207.7434) 
(list 1920.5625 -197.357) 
(list 1920.5625 -196.357) 
(list 1920.5625 -196.357) 
(list 1920.2625 -186.357) 
(list 1919.7375 -186.357) 
(list 1919.4375 -196.357) 
(list 1919.4375 -196.357) 
(list 1919.4375 -197.357) 
(list 1845.415 -207.7434) 
(list 1845.415 -212.6864) 
(list 1919.4375 -200.8) 
(list 1919.4375 -201.8) 
(list 1919.4375 -201.8) 
(list 1919.815 -211.8)))
(apply 'command (append '("pline") coords '("c")))
(setq currobj (ssadd (entlast) currobj))
(command "_layer" "set" "prebias" "")
(setq coords (list 
(list 1919.4375 -212.6864) 
(list 1919.4375 -200.8) 
(list 1845.415 -212.6864) 
(list 1845.415 -207.7434) 
(list 1919.4375 -197.357) 
(list 1919.4375 -186.357) 
(list 1920.5625 -186.357) 
(list 1920.5625 -197.357) 
(list 1994.585 -207.7434) 
(list 1994.585 -212.6864) 
(list 1920.5625 -200.8) 
(list 1920.5625 -212.6864)))
(apply 'command (append '("pline") coords '("c")))
(setq currobj (ssadd (entlast) currobj))
(command "_layer" "set" "nitride" "")
(command "_layer" "set" "fda1" "")
(setq coords (list 
(list 1920.5625 -200.657) 
(list 1994.585 -212.5434) 
(list 1994.585 -212.3664) 
(list 1920.5625 -200.58)))
(apply 'command (append '("pline") coords '("c")))
(setq currobj (ssadd (entlast) currobj))
(setq coords (list 
(list 1920.5625 -200.437) 
(list 1994.585 -212.2234) 
(list 1994.585 -212.0464) 
(list 1920.5625 -200.36)))
(apply 'command (append '("pline") coords '("c")))
(setq currobj (ssadd (entlast) currobj))
(setq coords (list 
(list 1920.5625 -200.217) 
(list 1994.585 -211.9034) 
(list 1994.585 -211.7264) 
(list 1920.5625 -200.14)))
(apply 'command (append '("pline") coords '("c")))
(setq currobj (ssadd (entlast) currobj))
(setq coords (list 
(list 1920.5625 -199.997) 
(list 1994.585 -211.5834) 
(list 1994.585 -211.4064) 
(list 1920.5625 -199.92)))
(apply 'command (append '("pline") coords '("c")))
(setq currobj (ssadd (entlast) currobj))
(setq coords (list 
(list 1920.5625 -199.777) 
(list 1994.585 -211.2634) 
(list 1994.585 -211.0864) 
(list 1920.5625 -199.7)))
(apply 'command (append '("pline") coords '("c")))
(setq currobj (ssadd (entlast) currobj))
(setq coords (list 
(list 1920.5625 -199.557) 
(list 1994.585 -210.9434) 
(list 1994.585 -210.7664) 
(list 1920.5625 -199.48)))
(apply 'command (append '("pline") coords '("c")))
(setq currobj (ssadd (entlast) currobj))
(setq coords (list 
(list 1920.5625 -199.337) 
(list 1994.585 -210.6234) 
(list 1994.585 -210.4464) 
(list 1920.5625 -199.26)))
(apply 'command (append '("pline") coords '("c")))
(setq currobj (ssadd (entlast) currobj))
(setq coords (list 
(list 1920.5625 -199.117) 
(list 1994.585 -210.3034) 
(list 1994.585 -210.1264) 
(list 1920.5625 -199.04)))
(apply 'command (append '("pline") coords '("c")))
(setq currobj (ssadd (entlast) currobj))
(setq coords (list 
(list 1920.5625 -198.897) 
(list 1994.585 -209.9834) 
(list 1994.585 -209.8064) 
(list 1920.5625 -198.82)))
(apply 'command (append '("pline") coords '("c")))
(setq currobj (ssadd (entlast) currobj))
(setq coords (list 
(list 1920.5625 -198.677) 
(list 1994.585 -209.6634) 
(list 1994.585 -209.4864) 
(list 1920.5625 -198.6)))
(apply 'command (append '("pline") coords '("c")))
(setq currobj (ssadd (entlast) currobj))
(setq coords (list 
(list 1920.5625 -198.457) 
(list 1994.585 -209.3434) 
(list 1994.585 -209.1664) 
(list 1920.5625 -198.38)))
(apply 'command (append '("pline") coords '("c")))
(setq currobj (ssadd (entlast) currobj))
(setq coords (list 
(list 1920.5625 -198.237) 
(list 1994.585 -209.0234) 
(list 1994.585 -208.8464) 
(list 1920.5625 -198.16)))
(apply 'command (append '("pline") coords '("c")))
(setq currobj (ssadd (entlast) currobj))
(setq coords (list 
(list 1920.5625 -198.017) 
(list 1994.585 -208.7034) 
(list 1994.585 -208.5264) 
(list 1920.5625 -197.94)))
(apply 'command (append '("pline") coords '("c")))
(setq currobj (ssadd (entlast) currobj))
(setq coords (list 
(list 1920.5625 -197.797) 
(list 1994.585 -208.3834) 
(list 1994.585 -208.2064) 
(list 1920.5625 -197.72)))
(apply 'command (append '("pline") coords '("c")))
(setq currobj (ssadd (entlast) currobj))
(setq coords (list 
(list 1920.5625 -197.577) 
(list 1994.585 -208.0634) 
(list 1994.585 -207.8864) 
(list 1920.5625 -197.5)))
(apply 'command (append '("pline") coords '("c")))
(setq currobj (ssadd (entlast) currobj))
(setq coords (list 
(list 1919.4375 -197.5) 
(list 1845.415 -207.8864) 
(list 1845.415 -208.0634) 
(list 1919.4375 -197.577)))
(apply 'command (append '("pline") coords '("c")))
(setq currobj (ssadd (entlast) currobj))
(setq coords (list 
(list 1919.4375 -197.72) 
(list 1845.415 -208.2064) 
(list 1845.415 -208.3834) 
(list 1919.4375 -197.797)))
(apply 'command (append '("pline") coords '("c")))
(setq currobj (ssadd (entlast) currobj))
(setq coords (list 
(list 1919.4375 -197.94) 
(list 1845.415 -208.5264) 
(list 1845.415 -208.7034) 
(list 1919.4375 -198.017)))
(apply 'command (append '("pline") coords '("c")))
(setq currobj (ssadd (entlast) currobj))
(setq coords (list 
(list 1919.4375 -198.16) 
(list 1845.415 -208.8464) 
(list 1845.415 -209.0234) 
(list 1919.4375 -198.237)))
(apply 'command (append '("pline") coords '("c")))
(setq currobj (ssadd (entlast) currobj))
(setq coords (list 
(list 1919.4375 -198.38) 
(list 1845.415 -209.1664) 
(list 1845.415 -209.3434) 
(list 1919.4375 -198.457)))
(apply 'command (append '("pline") coords '("c")))
(setq currobj (ssadd (entlast) currobj))
(setq coords (list 
(list 1919.4375 -198.6) 
(list 1845.415 -209.4864) 
(list 1845.415 -209.6634) 
(list 1919.4375 -198.677)))
(apply 'command (append '("pline") coords '("c")))
(setq currobj (ssadd (entlast) currobj))
(setq coords (list 
(list 1919.4375 -198.82) 
(list 1845.415 -209.8064) 
(list 1845.415 -209.9834) 
(list 1919.4375 -198.897)))
(apply 'command (append '("pline") coords '("c")))
(setq currobj (ssadd (entlast) currobj))
(setq coords (list 
(list 1919.4375 -199.04) 
(list 1845.415 -210.1264) 
(list 1845.415 -210.3034) 
(list 1919.4375 -199.117)))
(apply 'command (append '("pline") coords '("c")))
(setq currobj (ssadd (entlast) currobj))
(setq coords (list 
(list 1919.4375 -199.26) 
(list 1845.415 -210.4464) 
(list 1845.415 -210.6234) 
(list 1919.4375 -199.337)))
(apply 'command (append '("pline") coords '("c")))
(setq currobj (ssadd (entlast) currobj))
(setq coords (list 
(list 1919.4375 -199.48) 
(list 1845.415 -210.7664) 
(list 1845.415 -210.9434) 
(list 1919.4375 -199.557)))
(apply 'command (append '("pline") coords '("c")))
(setq currobj (ssadd (entlast) currobj))
(setq coords (list 
(list 1919.4375 -199.7) 
(list 1845.415 -211.0864) 
(list 1845.415 -211.2634) 
(list 1919.4375 -199.777)))
(apply 'command (append '("pline") coords '("c")))
(setq currobj (ssadd (entlast) currobj))
(setq coords (list 
(list 1919.4375 -199.92) 
(list 1845.415 -211.4064) 
(list 1845.415 -211.5834) 
(list 1919.4375 -199.997)))
(apply 'command (append '("pline") coords '("c")))
(setq currobj (ssadd (entlast) currobj))
(setq coords (list 
(list 1919.4375 -200.14) 
(list 1845.415 -211.7264) 
(list 1845.415 -211.9034) 
(list 1919.4375 -200.217)))
(apply 'command (append '("pline") coords '("c")))
(setq currobj (ssadd (entlast) currobj))
(setq coords (list 
(list 1919.4375 -200.36) 
(list 1845.415 -212.0464) 
(list 1845.415 -212.2234) 
(list 1919.4375 -200.437)))
(apply 'command (append '("pline") coords '("c")))
(setq currobj (ssadd (entlast) currobj))
(setq coords (list 
(list 1919.4375 -200.58) 
(list 1845.415 -212.3664) 
(list 1845.415 -212.5434) 
(list 1919.4375 -200.657)))
(apply 'command (append '("pline") coords '("c")))
(setq currobj (ssadd (entlast) currobj))
(command "_layer" "set" "nitride" "")
(command "_layer" "set" "text" "")
(command "_circle" "1918.985,-211.8" "0.075")
(command "_circle" "1918.985,-211.5" "0.075")
(command "_circle" "1918.985,-211.2" "0.075")
(command "_circle" "1918.985,-210.9" "0.075")
(command "_circle" "1918.985,-210.6" "0.075")
(command "_circle" "1918.685,-211.8" "0.075")
(command "_circle" "1918.685,-211.5" "0.075")
(command "_circle" "1918.685,-211.2" "0.075")
(command "_circle" "1918.685,-210.9" "0.075")
(command "_circle" "1918.685,-210.6" "0.075")
(command "_circle" "1918.385,-211.8" "0.075")
(command "_circle" "1918.385,-211.5" "0.075")
(command "_circle" "1918.385,-211.2" "0.075")
(command "_circle" "1918.385,-210.9" "0.075")
(command "_circle" "1918.385,-210.6" "0.075")
(command "_circle" "1918.085,-211.8" "0.075")
(command "_circle" "1918.085,-211.5" "0.075")
(command "_circle" "1918.085,-211.2" "0.075")
(command "_circle" "1918.085,-210.9" "0.075")
(command "_circle" "1918.085,-210.6" "0.075")
(command "_circle" "1917.785,-211.8" "0.075")
(command "_circle" "1917.785,-211.5" "0.075")
(command "_circle" "1917.785,-211.2" "0.075")
(command "_circle" "1917.785,-210.9" "0.075")
(command "_circle" "1917.785,-210.6" "0.075")
(command "_layer" "set" "nitride" "")
(setq anglednodearray6 currobj)
(setq currobj nil)
(setq currobj (ssadd))
; DRAWING COOLED SINGLE NANOBEAM
(setq coords (list 
(list 1920.2625 -186.357) 
(list 1920.2625 -181.357) 
(list 1919.7375 -181.357) 
(list 1919.7375 -186.357)))
(apply 'command (append '("pline") coords '("c")))
(setq currobj (ssadd (entlast) currobj))
(command "_layer" "set" "prebias" "")
(command "_rectangle" "1919.7375,-186.357" "1920.2625,-181.357")
(setq currobj (ssadd (entlast) currobj))
(command "_layer" "set" "nitride" "")
(setq coords (list 
(list 1920.2625 -181.357) 
(list 1920.5625 -171.357) 
(list 1920.5625 -171.357) 
(list 1920.5625 -170.357) 
(list 1994.585 -171.107) 
(list 1994.585 -166.164) 
(list 1920.5625 -166.914) 
(list 1920.5625 -165.914) 
(list 1920.5625 -165.914) 
(list 1920.2625 -155.914) 
(list 1919.7375 -155.914) 
(list 1919.4375 -165.914) 
(list 1919.4375 -165.914) 
(list 1919.4375 -166.914) 
(list 1845.415 -166.164) 
(list 1845.415 -171.107) 
(list 1919.4375 -170.357) 
(list 1919.4375 -171.357) 
(list 1919.4375 -171.357) 
(list 1919.7375 -181.357)))
(apply 'command (append '("pline") coords '("c")))
(setq currobj (ssadd (entlast) currobj))
(command "_layer" "set" "prebias" "")
(setq coords (list 
(list 1919.4375 -181.357) 
(list 1919.4375 -170.357) 
(list 1845.415 -171.107) 
(list 1845.415 -166.164) 
(list 1919.4375 -166.914) 
(list 1919.4375 -155.914) 
(list 1920.5625 -155.914) 
(list 1920.5625 -166.914) 
(list 1994.585 -166.164) 
(list 1994.585 -171.107) 
(list 1920.5625 -170.357) 
(list 1920.5625 -181.357)))
(apply 'command (append '("pline") coords '("c")))
(setq currobj (ssadd (entlast) currobj))
(command "_layer" "set" "nitride" "")
(command "_layer" "set" "fda1" "")
(setq coords (list 
(list 1920.5625 -170.214) 
(list 1994.585 -170.964) 
(list 1994.585 -170.787) 
(list 1920.5625 -170.137)))
(apply 'command (append '("pline") coords '("c")))
(setq currobj (ssadd (entlast) currobj))
(setq coords (list 
(list 1920.5625 -169.994) 
(list 1994.585 -170.644) 
(list 1994.585 -170.467) 
(list 1920.5625 -169.917)))
(apply 'command (append '("pline") coords '("c")))
(setq currobj (ssadd (entlast) currobj))
(setq coords (list 
(list 1920.5625 -169.774) 
(list 1994.585 -170.324) 
(list 1994.585 -170.147) 
(list 1920.5625 -169.697)))
(apply 'command (append '("pline") coords '("c")))
(setq currobj (ssadd (entlast) currobj))
(setq coords (list 
(list 1920.5625 -169.554) 
(list 1994.585 -170.004) 
(list 1994.585 -169.827) 
(list 1920.5625 -169.477)))
(apply 'command (append '("pline") coords '("c")))
(setq currobj (ssadd (entlast) currobj))
(setq coords (list 
(list 1920.5625 -169.334) 
(list 1994.585 -169.684) 
(list 1994.585 -169.507) 
(list 1920.5625 -169.257)))
(apply 'command (append '("pline") coords '("c")))
(setq currobj (ssadd (entlast) currobj))
(setq coords (list 
(list 1920.5625 -169.114) 
(list 1994.585 -169.364) 
(list 1994.585 -169.187) 
(list 1920.5625 -169.037)))
(apply 'command (append '("pline") coords '("c")))
(setq currobj (ssadd (entlast) currobj))
(setq coords (list 
(list 1920.5625 -168.894) 
(list 1994.585 -169.044) 
(list 1994.585 -168.867) 
(list 1920.5625 -168.817)))
(apply 'command (append '("pline") coords '("c")))
(setq currobj (ssadd (entlast) currobj))
(setq coords (list 
(list 1920.5625 -168.674) 
(list 1994.585 -168.724) 
(list 1994.585 -168.547) 
(list 1920.5625 -168.597)))
(apply 'command (append '("pline") coords '("c")))
(setq currobj (ssadd (entlast) currobj))
(setq coords (list 
(list 1920.5625 -168.454) 
(list 1994.585 -168.404) 
(list 1994.585 -168.227) 
(list 1920.5625 -168.377)))
(apply 'command (append '("pline") coords '("c")))
(setq currobj (ssadd (entlast) currobj))
(setq coords (list 
(list 1920.5625 -168.234) 
(list 1994.585 -168.084) 
(list 1994.585 -167.907) 
(list 1920.5625 -168.157)))
(apply 'command (append '("pline") coords '("c")))
(setq currobj (ssadd (entlast) currobj))
(setq coords (list 
(list 1920.5625 -168.014) 
(list 1994.585 -167.764) 
(list 1994.585 -167.587) 
(list 1920.5625 -167.937)))
(apply 'command (append '("pline") coords '("c")))
(setq currobj (ssadd (entlast) currobj))
(setq coords (list 
(list 1920.5625 -167.794) 
(list 1994.585 -167.444) 
(list 1994.585 -167.267) 
(list 1920.5625 -167.717)))
(apply 'command (append '("pline") coords '("c")))
(setq currobj (ssadd (entlast) currobj))
(setq coords (list 
(list 1920.5625 -167.574) 
(list 1994.585 -167.124) 
(list 1994.585 -166.947) 
(list 1920.5625 -167.497)))
(apply 'command (append '("pline") coords '("c")))
(setq currobj (ssadd (entlast) currobj))
(setq coords (list 
(list 1920.5625 -167.354) 
(list 1994.585 -166.804) 
(list 1994.585 -166.627) 
(list 1920.5625 -167.277)))
(apply 'command (append '("pline") coords '("c")))
(setq currobj (ssadd (entlast) currobj))
(setq coords (list 
(list 1920.5625 -167.134) 
(list 1994.585 -166.484) 
(list 1994.585 -166.307) 
(list 1920.5625 -167.057)))
(apply 'command (append '("pline") coords '("c")))
(setq currobj (ssadd (entlast) currobj))
(setq coords (list 
(list 1919.4375 -167.057) 
(list 1845.415 -166.307) 
(list 1845.415 -166.484) 
(list 1919.4375 -167.134)))
(apply 'command (append '("pline") coords '("c")))
(setq currobj (ssadd (entlast) currobj))
(setq coords (list 
(list 1919.4375 -167.277) 
(list 1845.415 -166.627) 
(list 1845.415 -166.804) 
(list 1919.4375 -167.354)))
(apply 'command (append '("pline") coords '("c")))
(setq currobj (ssadd (entlast) currobj))
(setq coords (list 
(list 1919.4375 -167.497) 
(list 1845.415 -166.947) 
(list 1845.415 -167.124) 
(list 1919.4375 -167.574)))
(apply 'command (append '("pline") coords '("c")))
(setq currobj (ssadd (entlast) currobj))
(setq coords (list 
(list 1919.4375 -167.717) 
(list 1845.415 -167.267) 
(list 1845.415 -167.444) 
(list 1919.4375 -167.794)))
(apply 'command (append '("pline") coords '("c")))
(setq currobj (ssadd (entlast) currobj))
(setq coords (list 
(list 1919.4375 -167.937) 
(list 1845.415 -167.587) 
(list 1845.415 -167.764) 
(list 1919.4375 -168.014)))
(apply 'command (append '("pline") coords '("c")))
(setq currobj (ssadd (entlast) currobj))
(setq coords (list 
(list 1919.4375 -168.157) 
(list 1845.415 -167.907) 
(list 1845.415 -168.084) 
(list 1919.4375 -168.234)))
(apply 'command (append '("pline") coords '("c")))
(setq currobj (ssadd (entlast) currobj))
(setq coords (list 
(list 1919.4375 -168.377) 
(list 1845.415 -168.227) 
(list 1845.415 -168.404) 
(list 1919.4375 -168.454)))
(apply 'command (append '("pline") coords '("c")))
(setq currobj (ssadd (entlast) currobj))
(setq coords (list 
(list 1919.4375 -168.597) 
(list 1845.415 -168.547) 
(list 1845.415 -168.724) 
(list 1919.4375 -168.674)))
(apply 'command (append '("pline") coords '("c")))
(setq currobj (ssadd (entlast) currobj))
(setq coords (list 
(list 1919.4375 -168.817) 
(list 1845.415 -168.867) 
(list 1845.415 -169.044) 
(list 1919.4375 -168.894)))
(apply 'command (append '("pline") coords '("c")))
(setq currobj (ssadd (entlast) currobj))
(setq coords (list 
(list 1919.4375 -169.037) 
(list 1845.415 -169.187) 
(list 1845.415 -169.364) 
(list 1919.4375 -169.114)))
(apply 'command (append '("pline") coords '("c")))
(setq currobj (ssadd (entlast) currobj))
(setq coords (list 
(list 1919.4375 -169.257) 
(list 1845.415 -169.507) 
(list 1845.415 -169.684) 
(list 1919.4375 -169.334)))
(apply 'command (append '("pline") coords '("c")))
(setq currobj (ssadd (entlast) currobj))
(setq coords (list 
(list 1919.4375 -169.477) 
(list 1845.415 -169.827) 
(list 1845.415 -170.004) 
(list 1919.4375 -169.554)))
(apply 'command (append '("pline") coords '("c")))
(setq currobj (ssadd (entlast) currobj))
(setq coords (list 
(list 1919.4375 -169.697) 
(list 1845.415 -170.147) 
(list 1845.415 -170.324) 
(list 1919.4375 -169.774)))
(apply 'command (append '("pline") coords '("c")))
(setq currobj (ssadd (entlast) currobj))
(setq coords (list 
(list 1919.4375 -169.917) 
(list 1845.415 -170.467) 
(list 1845.415 -170.644) 
(list 1919.4375 -169.994)))
(apply 'command (append '("pline") coords '("c")))
(setq currobj (ssadd (entlast) currobj))
(setq coords (list 
(list 1919.4375 -170.137) 
(list 1845.415 -170.787) 
(list 1845.415 -170.964) 
(list 1919.4375 -170.214)))
(apply 'command (append '("pline") coords '("c")))
(setq currobj (ssadd (entlast) currobj))
(command "_layer" "set" "nitride" "")
(command "_layer" "set" "text" "")
(command "_circle" "1919.0625,-181.357" "0.075")
(command "_circle" "1919.0625,-181.057" "0.075")
(command "_circle" "1919.0625,-180.757" "0.075")
(command "_circle" "1919.0625,-180.457" "0.075")
(command "_circle" "1919.0625,-180.157" "0.075")
(command "_circle" "1918.7625,-181.357" "0.075")
(command "_circle" "1918.7625,-181.057" "0.075")
(command "_circle" "1918.7625,-180.757" "0.075")
(command "_circle" "1918.7625,-180.457" "0.075")
(command "_circle" "1918.7625,-180.157" "0.075")
(command "_circle" "1918.4625,-181.357" "0.075")
(command "_circle" "1918.4625,-181.057" "0.075")
(command "_circle" "1918.4625,-180.757" "0.075")
(command "_circle" "1918.4625,-180.457" "0.075")
(command "_circle" "1918.4625,-180.157" "0.075")
(command "_circle" "1918.1625,-181.357" "0.075")
(command "_circle" "1918.1625,-181.057" "0.075")
(command "_circle" "1918.1625,-180.757" "0.075")
(command "_circle" "1918.1625,-180.457" "0.075")
(command "_circle" "1918.1625,-180.157" "0.075")
(command "_circle" "1917.8625,-181.357" "0.075")
(command "_circle" "1917.8625,-181.057" "0.075")
(command "_circle" "1917.8625,-180.757" "0.075")
(command "_circle" "1917.8625,-180.457" "0.075")
(command "_circle" "1917.8625,-180.157" "0.075")
(command "_layer" "set" "nitride" "")
(setq coords (list 
(list 1920.2625 -155.914) 
(list 1920.2625 -40.2693) 
(list 1919.7375 -40.2693) 
(list 1919.7375 -155.914)))
(apply 'command (append '("pline") coords '("c")))
(setq currobj (ssadd (entlast) currobj))
(command "_layer" "set" "prebias" "")
(command "_rectangle" "1919.7375,-155.914" "1920.2625,-40.2693")
(setq currobj (ssadd (entlast) currobj))
(command "_layer" "set" "nitride" "")
(setq coords (list 
(list 1920.2625 -40.2693) 
(list 1920.5625 -30.2693) 
(list 1920.5625 -30.2693) 
(list 1920.5625 -29.2693) 
(list 1994.585 -30.0193) 
(list 1994.585 -25.0763) 
(list 1920.5625 -25.8263) 
(list 1920.5625 -24.8263) 
(list 1920.5625 -24.8263) 
(list 1920.2625 -14.8263) 
(list 1919.7375 -14.8263) 
(list 1919.4375 -24.8263) 
(list 1919.4375 -24.8263) 
(list 1919.4375 -25.8263) 
(list 1845.415 -25.0763) 
(list 1845.415 -30.0193) 
(list 1919.4375 -29.2693) 
(list 1919.4375 -30.2693) 
(list 1919.4375 -30.2693) 
(list 1919.7375 -40.2693)))
(apply 'command (append '("pline") coords '("c")))
(setq currobj (ssadd (entlast) currobj))
(command "_layer" "set" "prebias" "")
(setq coords (list 
(list 1919.4375 -40.2693) 
(list 1919.4375 -29.2693) 
(list 1845.415 -30.0193) 
(list 1845.415 -25.0763) 
(list 1919.4375 -25.8263) 
(list 1919.4375 -14.8263) 
(list 1920.5625 -14.8263) 
(list 1920.5625 -25.8263) 
(list 1994.585 -25.0763) 
(list 1994.585 -30.0193) 
(list 1920.5625 -29.2693) 
(list 1920.5625 -40.2693)))
(apply 'command (append '("pline") coords '("c")))
(setq currobj (ssadd (entlast) currobj))
(command "_layer" "set" "nitride" "")
(command "_layer" "set" "fda1" "")
(setq coords (list 
(list 1920.5625 -29.1263) 
(list 1994.585 -29.8763) 
(list 1994.585 -29.6993) 
(list 1920.5625 -29.0493)))
(apply 'command (append '("pline") coords '("c")))
(setq currobj (ssadd (entlast) currobj))
(setq coords (list 
(list 1920.5625 -28.9063) 
(list 1994.585 -29.5563) 
(list 1994.585 -29.3793) 
(list 1920.5625 -28.8293)))
(apply 'command (append '("pline") coords '("c")))
(setq currobj (ssadd (entlast) currobj))
(setq coords (list 
(list 1920.5625 -28.6863) 
(list 1994.585 -29.2363) 
(list 1994.585 -29.0593) 
(list 1920.5625 -28.6093)))
(apply 'command (append '("pline") coords '("c")))
(setq currobj (ssadd (entlast) currobj))
(setq coords (list 
(list 1920.5625 -28.4663) 
(list 1994.585 -28.9163) 
(list 1994.585 -28.7393) 
(list 1920.5625 -28.3893)))
(apply 'command (append '("pline") coords '("c")))
(setq currobj (ssadd (entlast) currobj))
(setq coords (list 
(list 1920.5625 -28.2463) 
(list 1994.585 -28.5963) 
(list 1994.585 -28.4193) 
(list 1920.5625 -28.1693)))
(apply 'command (append '("pline") coords '("c")))
(setq currobj (ssadd (entlast) currobj))
(setq coords (list 
(list 1920.5625 -28.0263) 
(list 1994.585 -28.2763) 
(list 1994.585 -28.0993) 
(list 1920.5625 -27.9493)))
(apply 'command (append '("pline") coords '("c")))
(setq currobj (ssadd (entlast) currobj))
(setq coords (list 
(list 1920.5625 -27.8063) 
(list 1994.585 -27.9563) 
(list 1994.585 -27.7793) 
(list 1920.5625 -27.7293)))
(apply 'command (append '("pline") coords '("c")))
(setq currobj (ssadd (entlast) currobj))
(setq coords (list 
(list 1920.5625 -27.5863) 
(list 1994.585 -27.6363) 
(list 1994.585 -27.4593) 
(list 1920.5625 -27.5093)))
(apply 'command (append '("pline") coords '("c")))
(setq currobj (ssadd (entlast) currobj))
(setq coords (list 
(list 1920.5625 -27.3663) 
(list 1994.585 -27.3163) 
(list 1994.585 -27.1393) 
(list 1920.5625 -27.2893)))
(apply 'command (append '("pline") coords '("c")))
(setq currobj (ssadd (entlast) currobj))
(setq coords (list 
(list 1920.5625 -27.1463) 
(list 1994.585 -26.9963) 
(list 1994.585 -26.8193) 
(list 1920.5625 -27.0693)))
(apply 'command (append '("pline") coords '("c")))
(setq currobj (ssadd (entlast) currobj))
(setq coords (list 
(list 1920.5625 -26.9263) 
(list 1994.585 -26.6763) 
(list 1994.585 -26.4993) 
(list 1920.5625 -26.8493)))
(apply 'command (append '("pline") coords '("c")))
(setq currobj (ssadd (entlast) currobj))
(setq coords (list 
(list 1920.5625 -26.7063) 
(list 1994.585 -26.3563) 
(list 1994.585 -26.1793) 
(list 1920.5625 -26.6293)))
(apply 'command (append '("pline") coords '("c")))
(setq currobj (ssadd (entlast) currobj))
(setq coords (list 
(list 1920.5625 -26.4863) 
(list 1994.585 -26.0363) 
(list 1994.585 -25.8593) 
(list 1920.5625 -26.4093)))
(apply 'command (append '("pline") coords '("c")))
(setq currobj (ssadd (entlast) currobj))
(setq coords (list 
(list 1920.5625 -26.2663) 
(list 1994.585 -25.7163) 
(list 1994.585 -25.5393) 
(list 1920.5625 -26.1893)))
(apply 'command (append '("pline") coords '("c")))
(setq currobj (ssadd (entlast) currobj))
(setq coords (list 
(list 1920.5625 -26.0463) 
(list 1994.585 -25.3963) 
(list 1994.585 -25.2193) 
(list 1920.5625 -25.9693)))
(apply 'command (append '("pline") coords '("c")))
(setq currobj (ssadd (entlast) currobj))
(setq coords (list 
(list 1919.4375 -25.9693) 
(list 1845.415 -25.2193) 
(list 1845.415 -25.3963) 
(list 1919.4375 -26.0463)))
(apply 'command (append '("pline") coords '("c")))
(setq currobj (ssadd (entlast) currobj))
(setq coords (list 
(list 1919.4375 -26.1893) 
(list 1845.415 -25.5393) 
(list 1845.415 -25.7163) 
(list 1919.4375 -26.2663)))
(apply 'command (append '("pline") coords '("c")))
(setq currobj (ssadd (entlast) currobj))
(setq coords (list 
(list 1919.4375 -26.4093) 
(list 1845.415 -25.8593) 
(list 1845.415 -26.0363) 
(list 1919.4375 -26.4863)))
(apply 'command (append '("pline") coords '("c")))
(setq currobj (ssadd (entlast) currobj))
(setq coords (list 
(list 1919.4375 -26.6293) 
(list 1845.415 -26.1793) 
(list 1845.415 -26.3563) 
(list 1919.4375 -26.7063)))
(apply 'command (append '("pline") coords '("c")))
(setq currobj (ssadd (entlast) currobj))
(setq coords (list 
(list 1919.4375 -26.8493) 
(list 1845.415 -26.4993) 
(list 1845.415 -26.6763) 
(list 1919.4375 -26.9263)))
(apply 'command (append '("pline") coords '("c")))
(setq currobj (ssadd (entlast) currobj))
(setq coords (list 
(list 1919.4375 -27.0693) 
(list 1845.415 -26.8193) 
(list 1845.415 -26.9963) 
(list 1919.4375 -27.1463)))
(apply 'command (append '("pline") coords '("c")))
(setq currobj (ssadd (entlast) currobj))
(setq coords (list 
(list 1919.4375 -27.2893) 
(list 1845.415 -27.1393) 
(list 1845.415 -27.3163) 
(list 1919.4375 -27.3663)))
(apply 'command (append '("pline") coords '("c")))
(setq currobj (ssadd (entlast) currobj))
(setq coords (list 
(list 1919.4375 -27.5093) 
(list 1845.415 -27.4593) 
(list 1845.415 -27.6363) 
(list 1919.4375 -27.5863)))
(apply 'command (append '("pline") coords '("c")))
(setq currobj (ssadd (entlast) currobj))
(setq coords (list 
(list 1919.4375 -27.7293) 
(list 1845.415 -27.7793) 
(list 1845.415 -27.9563) 
(list 1919.4375 -27.8063)))
(apply 'command (append '("pline") coords '("c")))
(setq currobj (ssadd (entlast) currobj))
(setq coords (list 
(list 1919.4375 -27.9493) 
(list 1845.415 -28.0993) 
(list 1845.415 -28.2763) 
(list 1919.4375 -28.0263)))
(apply 'command (append '("pline") coords '("c")))
(setq currobj (ssadd (entlast) currobj))
(setq coords (list 
(list 1919.4375 -28.1693) 
(list 1845.415 -28.4193) 
(list 1845.415 -28.5963) 
(list 1919.4375 -28.2463)))
(apply 'command (append '("pline") coords '("c")))
(setq currobj (ssadd (entlast) currobj))
(setq coords (list 
(list 1919.4375 -28.3893) 
(list 1845.415 -28.7393) 
(list 1845.415 -28.9163) 
(list 1919.4375 -28.4663)))
(apply 'command (append '("pline") coords '("c")))
(setq currobj (ssadd (entlast) currobj))
(setq coords (list 
(list 1919.4375 -28.6093) 
(list 1845.415 -29.0593) 
(list 1845.415 -29.2363) 
(list 1919.4375 -28.6863)))
(apply 'command (append '("pline") coords '("c")))
(setq currobj (ssadd (entlast) currobj))
(setq coords (list 
(list 1919.4375 -28.8293) 
(list 1845.415 -29.3793) 
(list 1845.415 -29.5563) 
(list 1919.4375 -28.9063)))
(apply 'command (append '("pline") coords '("c")))
(setq currobj (ssadd (entlast) currobj))
(setq coords (list 
(list 1919.4375 -29.0493) 
(list 1845.415 -29.6993) 
(list 1845.415 -29.8763) 
(list 1919.4375 -29.1263)))
(apply 'command (append '("pline") coords '("c")))
(setq currobj (ssadd (entlast) currobj))
(command "_layer" "set" "nitride" "")
(command "_layer" "set" "text" "")
(command "_circle" "1919.0625,-40.2693" "0.075")
(command "_circle" "1919.0625,-39.9693" "0.075")
(command "_circle" "1919.0625,-39.6693" "0.075")
(command "_circle" "1919.0625,-39.3693" "0.075")
(command "_circle" "1919.0625,-39.0693" "0.075")
(command "_circle" "1918.7625,-40.2693" "0.075")
(command "_circle" "1918.7625,-39.9693" "0.075")
(command "_circle" "1918.7625,-39.6693" "0.075")
(command "_circle" "1918.7625,-39.3693" "0.075")
(command "_circle" "1918.7625,-39.0693" "0.075")
(command "_circle" "1918.4625,-40.2693" "0.075")
(command "_circle" "1918.4625,-39.9693" "0.075")
(command "_circle" "1918.4625,-39.6693" "0.075")
(command "_circle" "1918.4625,-39.3693" "0.075")
(command "_circle" "1918.4625,-39.0693" "0.075")
(command "_circle" "1918.1625,-40.2693" "0.075")
(command "_circle" "1918.1625,-39.9693" "0.075")
(command "_circle" "1918.1625,-39.6693" "0.075")
(command "_circle" "1918.1625,-39.3693" "0.075")
(command "_circle" "1918.1625,-39.0693" "0.075")
(command "_circle" "1917.8625,-40.2693" "0.075")
(command "_circle" "1917.8625,-39.9693" "0.075")
(command "_circle" "1917.8625,-39.6693" "0.075")
(command "_circle" "1917.8625,-39.3693" "0.075")
(command "_circle" "1917.8625,-39.0693" "0.075")
(command "_layer" "set" "nitride" "")
(setq coords (list 
(list 1920.2625 -14.8263) 
(list 1920.2625 100.8184) 
(list 1919.7375 100.8184) 
(list 1919.7375 -14.8263)))
(apply 'command (append '("pline") coords '("c")))
(setq currobj (ssadd (entlast) currobj))
(command "_layer" "set" "prebias" "")
(command "_rectangle" "1919.7375,-14.8263" "1920.2625,100.8184")
(setq currobj (ssadd (entlast) currobj))
(command "_layer" "set" "nitride" "")
(setq coords (list 
(list 1920.2625 100.8184) 
(list 1920.5625 110.8184) 
(list 1920.5625 110.8184) 
(list 1920.5625 111.8184) 
(list 1994.585 111.0684) 
(list 1994.585 116.0114) 
(list 1920.5625 115.2614) 
(list 1920.5625 116.2614) 
(list 1920.5625 116.2614) 
(list 1920.2625 126.2614) 
(list 1919.7375 126.2614) 
(list 1919.4375 116.2614) 
(list 1919.4375 116.2614) 
(list 1919.4375 115.2614) 
(list 1845.415 116.0114) 
(list 1845.415 111.0684) 
(list 1919.4375 111.8184) 
(list 1919.4375 110.8184) 
(list 1919.4375 110.8184) 
(list 1919.7375 100.8184)))
(apply 'command (append '("pline") coords '("c")))
(setq currobj (ssadd (entlast) currobj))
(command "_layer" "set" "prebias" "")
(setq coords (list 
(list 1919.4375 100.8184) 
(list 1919.4375 111.8184) 
(list 1845.415 111.0684) 
(list 1845.415 116.0114) 
(list 1919.4375 115.2614) 
(list 1919.4375 126.2614) 
(list 1920.5625 126.2614) 
(list 1920.5625 115.2614) 
(list 1994.585 116.0114) 
(list 1994.585 111.0684) 
(list 1920.5625 111.8184) 
(list 1920.5625 100.8184)))
(apply 'command (append '("pline") coords '("c")))
(setq currobj (ssadd (entlast) currobj))
(command "_layer" "set" "nitride" "")
(command "_layer" "set" "fda1" "")
(setq coords (list 
(list 1920.5625 111.9614) 
(list 1994.585 111.2114) 
(list 1994.585 111.3884) 
(list 1920.5625 112.0384)))
(apply 'command (append '("pline") coords '("c")))
(setq currobj (ssadd (entlast) currobj))
(setq coords (list 
(list 1920.5625 112.1814) 
(list 1994.585 111.5314) 
(list 1994.585 111.7084) 
(list 1920.5625 112.2584)))
(apply 'command (append '("pline") coords '("c")))
(setq currobj (ssadd (entlast) currobj))
(setq coords (list 
(list 1920.5625 112.4014) 
(list 1994.585 111.8514) 
(list 1994.585 112.0284) 
(list 1920.5625 112.4784)))
(apply 'command (append '("pline") coords '("c")))
(setq currobj (ssadd (entlast) currobj))
(setq coords (list 
(list 1920.5625 112.6214) 
(list 1994.585 112.1714) 
(list 1994.585 112.3484) 
(list 1920.5625 112.6984)))
(apply 'command (append '("pline") coords '("c")))
(setq currobj (ssadd (entlast) currobj))
(setq coords (list 
(list 1920.5625 112.8414) 
(list 1994.585 112.4914) 
(list 1994.585 112.6684) 
(list 1920.5625 112.9184)))
(apply 'command (append '("pline") coords '("c")))
(setq currobj (ssadd (entlast) currobj))
(setq coords (list 
(list 1920.5625 113.0614) 
(list 1994.585 112.8114) 
(list 1994.585 112.9884) 
(list 1920.5625 113.1384)))
(apply 'command (append '("pline") coords '("c")))
(setq currobj (ssadd (entlast) currobj))
(setq coords (list 
(list 1920.5625 113.2814) 
(list 1994.585 113.1314) 
(list 1994.585 113.3084) 
(list 1920.5625 113.3584)))
(apply 'command (append '("pline") coords '("c")))
(setq currobj (ssadd (entlast) currobj))
(setq coords (list 
(list 1920.5625 113.5014) 
(list 1994.585 113.4514) 
(list 1994.585 113.6284) 
(list 1920.5625 113.5784)))
(apply 'command (append '("pline") coords '("c")))
(setq currobj (ssadd (entlast) currobj))
(setq coords (list 
(list 1920.5625 113.7214) 
(list 1994.585 113.7714) 
(list 1994.585 113.9484) 
(list 1920.5625 113.7984)))
(apply 'command (append '("pline") coords '("c")))
(setq currobj (ssadd (entlast) currobj))
(setq coords (list 
(list 1920.5625 113.9414) 
(list 1994.585 114.0914) 
(list 1994.585 114.2684) 
(list 1920.5625 114.0184)))
(apply 'command (append '("pline") coords '("c")))
(setq currobj (ssadd (entlast) currobj))
(setq coords (list 
(list 1920.5625 114.1614) 
(list 1994.585 114.4114) 
(list 1994.585 114.5884) 
(list 1920.5625 114.2384)))
(apply 'command (append '("pline") coords '("c")))
(setq currobj (ssadd (entlast) currobj))
(setq coords (list 
(list 1920.5625 114.3814) 
(list 1994.585 114.7314) 
(list 1994.585 114.9084) 
(list 1920.5625 114.4584)))
(apply 'command (append '("pline") coords '("c")))
(setq currobj (ssadd (entlast) currobj))
(setq coords (list 
(list 1920.5625 114.6014) 
(list 1994.585 115.0514) 
(list 1994.585 115.2284) 
(list 1920.5625 114.6784)))
(apply 'command (append '("pline") coords '("c")))
(setq currobj (ssadd (entlast) currobj))
(setq coords (list 
(list 1920.5625 114.8214) 
(list 1994.585 115.3714) 
(list 1994.585 115.5484) 
(list 1920.5625 114.8984)))
(apply 'command (append '("pline") coords '("c")))
(setq currobj (ssadd (entlast) currobj))
(setq coords (list 
(list 1920.5625 115.0414) 
(list 1994.585 115.6914) 
(list 1994.585 115.8684) 
(list 1920.5625 115.1184)))
(apply 'command (append '("pline") coords '("c")))
(setq currobj (ssadd (entlast) currobj))
(setq coords (list 
(list 1919.4375 115.1184) 
(list 1845.415 115.8684) 
(list 1845.415 115.6914) 
(list 1919.4375 115.0414)))
(apply 'command (append '("pline") coords '("c")))
(setq currobj (ssadd (entlast) currobj))
(setq coords (list 
(list 1919.4375 114.8984) 
(list 1845.415 115.5484) 
(list 1845.415 115.3714) 
(list 1919.4375 114.8214)))
(apply 'command (append '("pline") coords '("c")))
(setq currobj (ssadd (entlast) currobj))
(setq coords (list 
(list 1919.4375 114.6784) 
(list 1845.415 115.2284) 
(list 1845.415 115.0514) 
(list 1919.4375 114.6014)))
(apply 'command (append '("pline") coords '("c")))
(setq currobj (ssadd (entlast) currobj))
(setq coords (list 
(list 1919.4375 114.4584) 
(list 1845.415 114.9084) 
(list 1845.415 114.7314) 
(list 1919.4375 114.3814)))
(apply 'command (append '("pline") coords '("c")))
(setq currobj (ssadd (entlast) currobj))
(setq coords (list 
(list 1919.4375 114.2384) 
(list 1845.415 114.5884) 
(list 1845.415 114.4114) 
(list 1919.4375 114.1614)))
(apply 'command (append '("pline") coords '("c")))
(setq currobj (ssadd (entlast) currobj))
(setq coords (list 
(list 1919.4375 114.0184) 
(list 1845.415 114.2684) 
(list 1845.415 114.0914) 
(list 1919.4375 113.9414)))
(apply 'command (append '("pline") coords '("c")))
(setq currobj (ssadd (entlast) currobj))
(setq coords (list 
(list 1919.4375 113.7984) 
(list 1845.415 113.9484) 
(list 1845.415 113.7714) 
(list 1919.4375 113.7214)))
(apply 'command (append '("pline") coords '("c")))
(setq currobj (ssadd (entlast) currobj))
(setq coords (list 
(list 1919.4375 113.5784) 
(list 1845.415 113.6284) 
(list 1845.415 113.4514) 
(list 1919.4375 113.5014)))
(apply 'command (append '("pline") coords '("c")))
(setq currobj (ssadd (entlast) currobj))
(setq coords (list 
(list 1919.4375 113.3584) 
(list 1845.415 113.3084) 
(list 1845.415 113.1314) 
(list 1919.4375 113.2814)))
(apply 'command (append '("pline") coords '("c")))
(setq currobj (ssadd (entlast) currobj))
(setq coords (list 
(list 1919.4375 113.1384) 
(list 1845.415 112.9884) 
(list 1845.415 112.8114) 
(list 1919.4375 113.0614)))
(apply 'command (append '("pline") coords '("c")))
(setq currobj (ssadd (entlast) currobj))
(setq coords (list 
(list 1919.4375 112.9184) 
(list 1845.415 112.6684) 
(list 1845.415 112.4914) 
(list 1919.4375 112.8414)))
(apply 'command (append '("pline") coords '("c")))
(setq currobj (ssadd (entlast) currobj))
(setq coords (list 
(list 1919.4375 112.6984) 
(list 1845.415 112.3484) 
(list 1845.415 112.1714) 
(list 1919.4375 112.6214)))
(apply 'command (append '("pline") coords '("c")))
(setq currobj (ssadd (entlast) currobj))
(setq coords (list 
(list 1919.4375 112.4784) 
(list 1845.415 112.0284) 
(list 1845.415 111.8514) 
(list 1919.4375 112.4014)))
(apply 'command (append '("pline") coords '("c")))
(setq currobj (ssadd (entlast) currobj))
(setq coords (list 
(list 1919.4375 112.2584) 
(list 1845.415 111.7084) 
(list 1845.415 111.5314) 
(list 1919.4375 112.1814)))
(apply 'command (append '("pline") coords '("c")))
(setq currobj (ssadd (entlast) currobj))
(setq coords (list 
(list 1919.4375 112.0384) 
(list 1845.415 111.3884) 
(list 1845.415 111.2114) 
(list 1919.4375 111.9614)))
(apply 'command (append '("pline") coords '("c")))
(setq currobj (ssadd (entlast) currobj))
(command "_layer" "set" "nitride" "")
(command "_layer" "set" "text" "")
(command "_circle" "1919.0625,100.8184" "0.075")
(command "_circle" "1919.0625,101.1184" "0.075")
(command "_circle" "1919.0625,101.4184" "0.075")
(command "_circle" "1919.0625,101.7184" "0.075")
(command "_circle" "1919.0625,102.0184" "0.075")
(command "_circle" "1918.7625,100.8184" "0.075")
(command "_circle" "1918.7625,101.1184" "0.075")
(command "_circle" "1918.7625,101.4184" "0.075")
(command "_circle" "1918.7625,101.7184" "0.075")
(command "_circle" "1918.7625,102.0184" "0.075")
(command "_circle" "1918.4625,100.8184" "0.075")
(command "_circle" "1918.4625,101.1184" "0.075")
(command "_circle" "1918.4625,101.4184" "0.075")
(command "_circle" "1918.4625,101.7184" "0.075")
(command "_circle" "1918.4625,102.0184" "0.075")
(command "_circle" "1918.1625,100.8184" "0.075")
(command "_circle" "1918.1625,101.1184" "0.075")
(command "_circle" "1918.1625,101.4184" "0.075")
(command "_circle" "1918.1625,101.7184" "0.075")
(command "_circle" "1918.1625,102.0184" "0.075")
(command "_circle" "1917.8625,100.8184" "0.075")
(command "_circle" "1917.8625,101.1184" "0.075")
(command "_circle" "1917.8625,101.4184" "0.075")
(command "_circle" "1917.8625,101.7184" "0.075")
(command "_circle" "1917.8625,102.0184" "0.075")
(command "_layer" "set" "nitride" "")
(setq coords (list 
(list 1920.2625 126.2614) 
(list 1920.2625 241.9061) 
(list 1919.7375 241.9061) 
(list 1919.7375 126.2614)))
(apply 'command (append '("pline") coords '("c")))
(setq currobj (ssadd (entlast) currobj))
(command "_layer" "set" "prebias" "")
(command "_rectangle" "1919.7375,126.2614" "1920.2625,241.9061")
(setq currobj (ssadd (entlast) currobj))
(command "_layer" "set" "nitride" "")
(setq coords (list 
(list 1920.2625 241.9061) 
(list 1920.5625 251.9061) 
(list 1920.5625 251.9061) 
(list 1920.5625 252.9061) 
(list 1994.585 252.1561) 
(list 1994.585 257.0991) 
(list 1920.5625 256.3491) 
(list 1920.5625 257.3491) 
(list 1920.5625 257.3491) 
(list 1920.2625 267.3491) 
(list 1919.7375 267.3491) 
(list 1919.4375 257.3491) 
(list 1919.4375 257.3491) 
(list 1919.4375 256.3491) 
(list 1845.415 257.0991) 
(list 1845.415 252.1561) 
(list 1919.4375 252.9061) 
(list 1919.4375 251.9061) 
(list 1919.4375 251.9061) 
(list 1919.7375 241.9061)))
(apply 'command (append '("pline") coords '("c")))
(setq currobj (ssadd (entlast) currobj))
(command "_layer" "set" "prebias" "")
(setq coords (list 
(list 1919.4375 241.9061) 
(list 1919.4375 252.9061) 
(list 1845.415 252.1561) 
(list 1845.415 257.0991) 
(list 1919.4375 256.3491) 
(list 1919.4375 267.3491) 
(list 1920.5625 267.3491) 
(list 1920.5625 256.3491) 
(list 1994.585 257.0991) 
(list 1994.585 252.1561) 
(list 1920.5625 252.9061) 
(list 1920.5625 241.9061)))
(apply 'command (append '("pline") coords '("c")))
(setq currobj (ssadd (entlast) currobj))
(command "_layer" "set" "nitride" "")
(command "_layer" "set" "fda1" "")
(setq coords (list 
(list 1920.5625 253.0491) 
(list 1994.585 252.2991) 
(list 1994.585 252.4761) 
(list 1920.5625 253.1261)))
(apply 'command (append '("pline") coords '("c")))
(setq currobj (ssadd (entlast) currobj))
(setq coords (list 
(list 1920.5625 253.2691) 
(list 1994.585 252.6191) 
(list 1994.585 252.7961) 
(list 1920.5625 253.3461)))
(apply 'command (append '("pline") coords '("c")))
(setq currobj (ssadd (entlast) currobj))
(setq coords (list 
(list 1920.5625 253.4891) 
(list 1994.585 252.9391) 
(list 1994.585 253.1161) 
(list 1920.5625 253.5661)))
(apply 'command (append '("pline") coords '("c")))
(setq currobj (ssadd (entlast) currobj))
(setq coords (list 
(list 1920.5625 253.7091) 
(list 1994.585 253.2591) 
(list 1994.585 253.4361) 
(list 1920.5625 253.7861)))
(apply 'command (append '("pline") coords '("c")))
(setq currobj (ssadd (entlast) currobj))
(setq coords (list 
(list 1920.5625 253.9291) 
(list 1994.585 253.5791) 
(list 1994.585 253.7561) 
(list 1920.5625 254.0061)))
(apply 'command (append '("pline") coords '("c")))
(setq currobj (ssadd (entlast) currobj))
(setq coords (list 
(list 1920.5625 254.1491) 
(list 1994.585 253.8991) 
(list 1994.585 254.0761) 
(list 1920.5625 254.2261)))
(apply 'command (append '("pline") coords '("c")))
(setq currobj (ssadd (entlast) currobj))
(setq coords (list 
(list 1920.5625 254.3691) 
(list 1994.585 254.2191) 
(list 1994.585 254.3961) 
(list 1920.5625 254.4461)))
(apply 'command (append '("pline") coords '("c")))
(setq currobj (ssadd (entlast) currobj))
(setq coords (list 
(list 1920.5625 254.5891) 
(list 1994.585 254.5391) 
(list 1994.585 254.7161) 
(list 1920.5625 254.6661)))
(apply 'command (append '("pline") coords '("c")))
(setq currobj (ssadd (entlast) currobj))
(setq coords (list 
(list 1920.5625 254.8091) 
(list 1994.585 254.8591) 
(list 1994.585 255.0361) 
(list 1920.5625 254.8861)))
(apply 'command (append '("pline") coords '("c")))
(setq currobj (ssadd (entlast) currobj))
(setq coords (list 
(list 1920.5625 255.0291) 
(list 1994.585 255.1791) 
(list 1994.585 255.3561) 
(list 1920.5625 255.1061)))
(apply 'command (append '("pline") coords '("c")))
(setq currobj (ssadd (entlast) currobj))
(setq coords (list 
(list 1920.5625 255.2491) 
(list 1994.585 255.4991) 
(list 1994.585 255.6761) 
(list 1920.5625 255.3261)))
(apply 'command (append '("pline") coords '("c")))
(setq currobj (ssadd (entlast) currobj))
(setq coords (list 
(list 1920.5625 255.4691) 
(list 1994.585 255.8191) 
(list 1994.585 255.9961) 
(list 1920.5625 255.5461)))
(apply 'command (append '("pline") coords '("c")))
(setq currobj (ssadd (entlast) currobj))
(setq coords (list 
(list 1920.5625 255.6891) 
(list 1994.585 256.1391) 
(list 1994.585 256.3161) 
(list 1920.5625 255.7661)))
(apply 'command (append '("pline") coords '("c")))
(setq currobj (ssadd (entlast) currobj))
(setq coords (list 
(list 1920.5625 255.9091) 
(list 1994.585 256.4591) 
(list 1994.585 256.6361) 
(list 1920.5625 255.9861)))
(apply 'command (append '("pline") coords '("c")))
(setq currobj (ssadd (entlast) currobj))
(setq coords (list 
(list 1920.5625 256.1291) 
(list 1994.585 256.7791) 
(list 1994.585 256.9561) 
(list 1920.5625 256.2061)))
(apply 'command (append '("pline") coords '("c")))
(setq currobj (ssadd (entlast) currobj))
(setq coords (list 
(list 1919.4375 256.2061) 
(list 1845.415 256.9561) 
(list 1845.415 256.7791) 
(list 1919.4375 256.1291)))
(apply 'command (append '("pline") coords '("c")))
(setq currobj (ssadd (entlast) currobj))
(setq coords (list 
(list 1919.4375 255.9861) 
(list 1845.415 256.6361) 
(list 1845.415 256.4591) 
(list 1919.4375 255.9091)))
(apply 'command (append '("pline") coords '("c")))
(setq currobj (ssadd (entlast) currobj))
(setq coords (list 
(list 1919.4375 255.7661) 
(list 1845.415 256.3161) 
(list 1845.415 256.1391) 
(list 1919.4375 255.6891)))
(apply 'command (append '("pline") coords '("c")))
(setq currobj (ssadd (entlast) currobj))
(setq coords (list 
(list 1919.4375 255.5461) 
(list 1845.415 255.9961) 
(list 1845.415 255.8191) 
(list 1919.4375 255.4691)))
(apply 'command (append '("pline") coords '("c")))
(setq currobj (ssadd (entlast) currobj))
(setq coords (list 
(list 1919.4375 255.3261) 
(list 1845.415 255.6761) 
(list 1845.415 255.4991) 
(list 1919.4375 255.2491)))
(apply 'command (append '("pline") coords '("c")))
(setq currobj (ssadd (entlast) currobj))
(setq coords (list 
(list 1919.4375 255.1061) 
(list 1845.415 255.3561) 
(list 1845.415 255.1791) 
(list 1919.4375 255.0291)))
(apply 'command (append '("pline") coords '("c")))
(setq currobj (ssadd (entlast) currobj))
(setq coords (list 
(list 1919.4375 254.8861) 
(list 1845.415 255.0361) 
(list 1845.415 254.8591) 
(list 1919.4375 254.8091)))
(apply 'command (append '("pline") coords '("c")))
(setq currobj (ssadd (entlast) currobj))
(setq coords (list 
(list 1919.4375 254.6661) 
(list 1845.415 254.7161) 
(list 1845.415 254.5391) 
(list 1919.4375 254.5891)))
(apply 'command (append '("pline") coords '("c")))
(setq currobj (ssadd (entlast) currobj))
(setq coords (list 
(list 1919.4375 254.4461) 
(list 1845.415 254.3961) 
(list 1845.415 254.2191) 
(list 1919.4375 254.3691)))
(apply 'command (append '("pline") coords '("c")))
(setq currobj (ssadd (entlast) currobj))
(setq coords (list 
(list 1919.4375 254.2261) 
(list 1845.415 254.0761) 
(list 1845.415 253.8991) 
(list 1919.4375 254.1491)))
(apply 'command (append '("pline") coords '("c")))
(setq currobj (ssadd (entlast) currobj))
(setq coords (list 
(list 1919.4375 254.0061) 
(list 1845.415 253.7561) 
(list 1845.415 253.5791) 
(list 1919.4375 253.9291)))
(apply 'command (append '("pline") coords '("c")))
(setq currobj (ssadd (entlast) currobj))
(setq coords (list 
(list 1919.4375 253.7861) 
(list 1845.415 253.4361) 
(list 1845.415 253.2591) 
(list 1919.4375 253.7091)))
(apply 'command (append '("pline") coords '("c")))
(setq currobj (ssadd (entlast) currobj))
(setq coords (list 
(list 1919.4375 253.5661) 
(list 1845.415 253.1161) 
(list 1845.415 252.9391) 
(list 1919.4375 253.4891)))
(apply 'command (append '("pline") coords '("c")))
(setq currobj (ssadd (entlast) currobj))
(setq coords (list 
(list 1919.4375 253.3461) 
(list 1845.415 252.7961) 
(list 1845.415 252.6191) 
(list 1919.4375 253.2691)))
(apply 'command (append '("pline") coords '("c")))
(setq currobj (ssadd (entlast) currobj))
(setq coords (list 
(list 1919.4375 253.1261) 
(list 1845.415 252.4761) 
(list 1845.415 252.2991) 
(list 1919.4375 253.0491)))
(apply 'command (append '("pline") coords '("c")))
(setq currobj (ssadd (entlast) currobj))
(command "_layer" "set" "nitride" "")
(command "_layer" "set" "text" "")
(command "_circle" "1919.0625,241.9061" "0.075")
(command "_circle" "1919.0625,242.2061" "0.075")
(command "_circle" "1919.0625,242.5061" "0.075")
(command "_circle" "1919.0625,242.8061" "0.075")
(command "_circle" "1919.0625,243.1061" "0.075")
(command "_circle" "1918.7625,241.9061" "0.075")
(command "_circle" "1918.7625,242.2061" "0.075")
(command "_circle" "1918.7625,242.5061" "0.075")
(command "_circle" "1918.7625,242.8061" "0.075")
(command "_circle" "1918.7625,243.1061" "0.075")
(command "_circle" "1918.4625,241.9061" "0.075")
(command "_circle" "1918.4625,242.2061" "0.075")
(command "_circle" "1918.4625,242.5061" "0.075")
(command "_circle" "1918.4625,242.8061" "0.075")
(command "_circle" "1918.4625,243.1061" "0.075")
(command "_circle" "1918.1625,241.9061" "0.075")
(command "_circle" "1918.1625,242.2061" "0.075")
(command "_circle" "1918.1625,242.5061" "0.075")
(command "_circle" "1918.1625,242.8061" "0.075")
(command "_circle" "1918.1625,243.1061" "0.075")
(command "_circle" "1917.8625,241.9061" "0.075")
(command "_circle" "1917.8625,242.2061" "0.075")
(command "_circle" "1917.8625,242.5061" "0.075")
(command "_circle" "1917.8625,242.8061" "0.075")
(command "_circle" "1917.8625,243.1061" "0.075")
(command "_layer" "set" "nitride" "")
(setq coords (list 
(list 1920.2625 267.3491) 
(list 1920.2625 382.9939) 
(list 1919.7375 382.9939) 
(list 1919.7375 267.3491)))
(apply 'command (append '("pline") coords '("c")))
(setq currobj (ssadd (entlast) currobj))
(command "_layer" "set" "prebias" "")
(command "_rectangle" "1919.7375,267.3491" "1920.2625,382.9939")
(setq currobj (ssadd (entlast) currobj))
(command "_layer" "set" "nitride" "")
(setq coords (list 
(list 1920.2625 382.9939) 
(list 1920.5625 392.9939) 
(list 1920.5625 392.9939) 
(list 1920.5625 393.9939) 
(list 1994.585 393.2439) 
(list 1994.585 398.1869) 
(list 1920.5625 397.4369) 
(list 1920.5625 398.4369) 
(list 1920.5625 398.4369) 
(list 1920.2625 408.4369) 
(list 1919.7375 408.4369) 
(list 1919.4375 398.4369) 
(list 1919.4375 398.4369) 
(list 1919.4375 397.4369) 
(list 1845.415 398.1869) 
(list 1845.415 393.2439) 
(list 1919.4375 393.9939) 
(list 1919.4375 392.9939) 
(list 1919.4375 392.9939) 
(list 1919.7375 382.9939)))
(apply 'command (append '("pline") coords '("c")))
(setq currobj (ssadd (entlast) currobj))
(command "_layer" "set" "prebias" "")
(setq coords (list 
(list 1919.4375 382.9939) 
(list 1919.4375 393.9939) 
(list 1845.415 393.2439) 
(list 1845.415 398.1869) 
(list 1919.4375 397.4369) 
(list 1919.4375 408.4369) 
(list 1920.5625 408.4369) 
(list 1920.5625 397.4369) 
(list 1994.585 398.1869) 
(list 1994.585 393.2439) 
(list 1920.5625 393.9939) 
(list 1920.5625 382.9939)))
(apply 'command (append '("pline") coords '("c")))
(setq currobj (ssadd (entlast) currobj))
(command "_layer" "set" "nitride" "")
(command "_layer" "set" "fda1" "")
(setq coords (list 
(list 1920.5625 394.1369) 
(list 1994.585 393.3869) 
(list 1994.585 393.5639) 
(list 1920.5625 394.2139)))
(apply 'command (append '("pline") coords '("c")))
(setq currobj (ssadd (entlast) currobj))
(setq coords (list 
(list 1920.5625 394.3569) 
(list 1994.585 393.7069) 
(list 1994.585 393.8839) 
(list 1920.5625 394.4339)))
(apply 'command (append '("pline") coords '("c")))
(setq currobj (ssadd (entlast) currobj))
(setq coords (list 
(list 1920.5625 394.5769) 
(list 1994.585 394.0269) 
(list 1994.585 394.2039) 
(list 1920.5625 394.6539)))
(apply 'command (append '("pline") coords '("c")))
(setq currobj (ssadd (entlast) currobj))
(setq coords (list 
(list 1920.5625 394.7969) 
(list 1994.585 394.3469) 
(list 1994.585 394.5239) 
(list 1920.5625 394.8739)))
(apply 'command (append '("pline") coords '("c")))
(setq currobj (ssadd (entlast) currobj))
(setq coords (list 
(list 1920.5625 395.0169) 
(list 1994.585 394.6669) 
(list 1994.585 394.8439) 
(list 1920.5625 395.0939)))
(apply 'command (append '("pline") coords '("c")))
(setq currobj (ssadd (entlast) currobj))
(setq coords (list 
(list 1920.5625 395.2369) 
(list 1994.585 394.9869) 
(list 1994.585 395.1639) 
(list 1920.5625 395.3139)))
(apply 'command (append '("pline") coords '("c")))
(setq currobj (ssadd (entlast) currobj))
(setq coords (list 
(list 1920.5625 395.4569) 
(list 1994.585 395.3069) 
(list 1994.585 395.4839) 
(list 1920.5625 395.5339)))
(apply 'command (append '("pline") coords '("c")))
(setq currobj (ssadd (entlast) currobj))
(setq coords (list 
(list 1920.5625 395.6769) 
(list 1994.585 395.6269) 
(list 1994.585 395.8039) 
(list 1920.5625 395.7539)))
(apply 'command (append '("pline") coords '("c")))
(setq currobj (ssadd (entlast) currobj))
(setq coords (list 
(list 1920.5625 395.8969) 
(list 1994.585 395.9469) 
(list 1994.585 396.1239) 
(list 1920.5625 395.9739)))
(apply 'command (append '("pline") coords '("c")))
(setq currobj (ssadd (entlast) currobj))
(setq coords (list 
(list 1920.5625 396.1169) 
(list 1994.585 396.2669) 
(list 1994.585 396.4439) 
(list 1920.5625 396.1939)))
(apply 'command (append '("pline") coords '("c")))
(setq currobj (ssadd (entlast) currobj))
(setq coords (list 
(list 1920.5625 396.3369) 
(list 1994.585 396.5869) 
(list 1994.585 396.7639) 
(list 1920.5625 396.4139)))
(apply 'command (append '("pline") coords '("c")))
(setq currobj (ssadd (entlast) currobj))
(setq coords (list 
(list 1920.5625 396.5569) 
(list 1994.585 396.9069) 
(list 1994.585 397.0839) 
(list 1920.5625 396.6339)))
(apply 'command (append '("pline") coords '("c")))
(setq currobj (ssadd (entlast) currobj))
(setq coords (list 
(list 1920.5625 396.7769) 
(list 1994.585 397.2269) 
(list 1994.585 397.4039) 
(list 1920.5625 396.8539)))
(apply 'command (append '("pline") coords '("c")))
(setq currobj (ssadd (entlast) currobj))
(setq coords (list 
(list 1920.5625 396.9969) 
(list 1994.585 397.5469) 
(list 1994.585 397.7239) 
(list 1920.5625 397.0739)))
(apply 'command (append '("pline") coords '("c")))
(setq currobj (ssadd (entlast) currobj))
(setq coords (list 
(list 1920.5625 397.2169) 
(list 1994.585 397.8669) 
(list 1994.585 398.0439) 
(list 1920.5625 397.2939)))
(apply 'command (append '("pline") coords '("c")))
(setq currobj (ssadd (entlast) currobj))
(setq coords (list 
(list 1919.4375 397.2939) 
(list 1845.415 398.0439) 
(list 1845.415 397.8669) 
(list 1919.4375 397.2169)))
(apply 'command (append '("pline") coords '("c")))
(setq currobj (ssadd (entlast) currobj))
(setq coords (list 
(list 1919.4375 397.0739) 
(list 1845.415 397.7239) 
(list 1845.415 397.5469) 
(list 1919.4375 396.9969)))
(apply 'command (append '("pline") coords '("c")))
(setq currobj (ssadd (entlast) currobj))
(setq coords (list 
(list 1919.4375 396.8539) 
(list 1845.415 397.4039) 
(list 1845.415 397.2269) 
(list 1919.4375 396.7769)))
(apply 'command (append '("pline") coords '("c")))
(setq currobj (ssadd (entlast) currobj))
(setq coords (list 
(list 1919.4375 396.6339) 
(list 1845.415 397.0839) 
(list 1845.415 396.9069) 
(list 1919.4375 396.5569)))
(apply 'command (append '("pline") coords '("c")))
(setq currobj (ssadd (entlast) currobj))
(setq coords (list 
(list 1919.4375 396.4139) 
(list 1845.415 396.7639) 
(list 1845.415 396.5869) 
(list 1919.4375 396.3369)))
(apply 'command (append '("pline") coords '("c")))
(setq currobj (ssadd (entlast) currobj))
(setq coords (list 
(list 1919.4375 396.1939) 
(list 1845.415 396.4439) 
(list 1845.415 396.2669) 
(list 1919.4375 396.1169)))
(apply 'command (append '("pline") coords '("c")))
(setq currobj (ssadd (entlast) currobj))
(setq coords (list 
(list 1919.4375 395.9739) 
(list 1845.415 396.1239) 
(list 1845.415 395.9469) 
(list 1919.4375 395.8969)))
(apply 'command (append '("pline") coords '("c")))
(setq currobj (ssadd (entlast) currobj))
(setq coords (list 
(list 1919.4375 395.7539) 
(list 1845.415 395.8039) 
(list 1845.415 395.6269) 
(list 1919.4375 395.6769)))
(apply 'command (append '("pline") coords '("c")))
(setq currobj (ssadd (entlast) currobj))
(setq coords (list 
(list 1919.4375 395.5339) 
(list 1845.415 395.4839) 
(list 1845.415 395.3069) 
(list 1919.4375 395.4569)))
(apply 'command (append '("pline") coords '("c")))
(setq currobj (ssadd (entlast) currobj))
(setq coords (list 
(list 1919.4375 395.3139) 
(list 1845.415 395.1639) 
(list 1845.415 394.9869) 
(list 1919.4375 395.2369)))
(apply 'command (append '("pline") coords '("c")))
(setq currobj (ssadd (entlast) currobj))
(setq coords (list 
(list 1919.4375 395.0939) 
(list 1845.415 394.8439) 
(list 1845.415 394.6669) 
(list 1919.4375 395.0169)))
(apply 'command (append '("pline") coords '("c")))
(setq currobj (ssadd (entlast) currobj))
(setq coords (list 
(list 1919.4375 394.8739) 
(list 1845.415 394.5239) 
(list 1845.415 394.3469) 
(list 1919.4375 394.7969)))
(apply 'command (append '("pline") coords '("c")))
(setq currobj (ssadd (entlast) currobj))
(setq coords (list 
(list 1919.4375 394.6539) 
(list 1845.415 394.2039) 
(list 1845.415 394.0269) 
(list 1919.4375 394.5769)))
(apply 'command (append '("pline") coords '("c")))
(setq currobj (ssadd (entlast) currobj))
(setq coords (list 
(list 1919.4375 394.4339) 
(list 1845.415 393.8839) 
(list 1845.415 393.7069) 
(list 1919.4375 394.3569)))
(apply 'command (append '("pline") coords '("c")))
(setq currobj (ssadd (entlast) currobj))
(setq coords (list 
(list 1919.4375 394.2139) 
(list 1845.415 393.5639) 
(list 1845.415 393.3869) 
(list 1919.4375 394.1369)))
(apply 'command (append '("pline") coords '("c")))
(setq currobj (ssadd (entlast) currobj))
(command "_layer" "set" "nitride" "")
(command "_layer" "set" "text" "")
(command "_circle" "1919.0625,382.9939" "0.075")
(command "_circle" "1919.0625,383.2939" "0.075")
(command "_circle" "1919.0625,383.5939" "0.075")
(command "_circle" "1919.0625,383.8939" "0.075")
(command "_circle" "1919.0625,384.1939" "0.075")
(command "_circle" "1918.7625,382.9939" "0.075")
(command "_circle" "1918.7625,383.2939" "0.075")
(command "_circle" "1918.7625,383.5939" "0.075")
(command "_circle" "1918.7625,383.8939" "0.075")
(command "_circle" "1918.7625,384.1939" "0.075")
(command "_circle" "1918.4625,382.9939" "0.075")
(command "_circle" "1918.4625,383.2939" "0.075")
(command "_circle" "1918.4625,383.5939" "0.075")
(command "_circle" "1918.4625,383.8939" "0.075")
(command "_circle" "1918.4625,384.1939" "0.075")
(command "_circle" "1918.1625,382.9939" "0.075")
(command "_circle" "1918.1625,383.2939" "0.075")
(command "_circle" "1918.1625,383.5939" "0.075")
(command "_circle" "1918.1625,383.8939" "0.075")
(command "_circle" "1918.1625,384.1939" "0.075")
(command "_circle" "1917.8625,382.9939" "0.075")
(command "_circle" "1917.8625,383.2939" "0.075")
(command "_circle" "1917.8625,383.5939" "0.075")
(command "_circle" "1917.8625,383.8939" "0.075")
(command "_circle" "1917.8625,384.1939" "0.075")
(command "_layer" "set" "nitride" "")
(setq coords (list 
(list 1920.2625 408.4369) 
(list 1920.2625 524.0816) 
(list 1919.7375 524.0816) 
(list 1919.7375 408.4369)))
(apply 'command (append '("pline") coords '("c")))
(setq currobj (ssadd (entlast) currobj))
(command "_layer" "set" "prebias" "")
(command "_rectangle" "1919.7375,408.4369" "1920.2625,524.0816")
(setq currobj (ssadd (entlast) currobj))
(command "_layer" "set" "nitride" "")
(setq coords (list 
(list 1920.2625 524.0816) 
(list 1920.5625 534.0816) 
(list 1920.5625 534.0816) 
(list 1920.5625 535.0816) 
(list 1994.585 534.3316) 
(list 1994.585 539.2746) 
(list 1920.5625 538.5246) 
(list 1920.5625 539.5246) 
(list 1920.5625 539.5246) 
(list 1920.2625 549.5246) 
(list 1919.7375 549.5246) 
(list 1919.4375 539.5246) 
(list 1919.4375 539.5246) 
(list 1919.4375 538.5246) 
(list 1845.415 539.2746) 
(list 1845.415 534.3316) 
(list 1919.4375 535.0816) 
(list 1919.4375 534.0816) 
(list 1919.4375 534.0816) 
(list 1919.7375 524.0816)))
(apply 'command (append '("pline") coords '("c")))
(setq currobj (ssadd (entlast) currobj))
(command "_layer" "set" "prebias" "")
(setq coords (list 
(list 1919.4375 524.0816) 
(list 1919.4375 535.0816) 
(list 1845.415 534.3316) 
(list 1845.415 539.2746) 
(list 1919.4375 538.5246) 
(list 1919.4375 549.5246) 
(list 1920.5625 549.5246) 
(list 1920.5625 538.5246) 
(list 1994.585 539.2746) 
(list 1994.585 534.3316) 
(list 1920.5625 535.0816) 
(list 1920.5625 524.0816)))
(apply 'command (append '("pline") coords '("c")))
(setq currobj (ssadd (entlast) currobj))
(command "_layer" "set" "nitride" "")
(command "_layer" "set" "fda1" "")
(setq coords (list 
(list 1920.5625 535.2246) 
(list 1994.585 534.4746) 
(list 1994.585 534.6516) 
(list 1920.5625 535.3016)))
(apply 'command (append '("pline") coords '("c")))
(setq currobj (ssadd (entlast) currobj))
(setq coords (list 
(list 1920.5625 535.4446) 
(list 1994.585 534.7946) 
(list 1994.585 534.9716) 
(list 1920.5625 535.5216)))
(apply 'command (append '("pline") coords '("c")))
(setq currobj (ssadd (entlast) currobj))
(setq coords (list 
(list 1920.5625 535.6646) 
(list 1994.585 535.1146) 
(list 1994.585 535.2916) 
(list 1920.5625 535.7416)))
(apply 'command (append '("pline") coords '("c")))
(setq currobj (ssadd (entlast) currobj))
(setq coords (list 
(list 1920.5625 535.8846) 
(list 1994.585 535.4346) 
(list 1994.585 535.6116) 
(list 1920.5625 535.9616)))
(apply 'command (append '("pline") coords '("c")))
(setq currobj (ssadd (entlast) currobj))
(setq coords (list 
(list 1920.5625 536.1046) 
(list 1994.585 535.7546) 
(list 1994.585 535.9316) 
(list 1920.5625 536.1816)))
(apply 'command (append '("pline") coords '("c")))
(setq currobj (ssadd (entlast) currobj))
(setq coords (list 
(list 1920.5625 536.3246) 
(list 1994.585 536.0746) 
(list 1994.585 536.2516) 
(list 1920.5625 536.4016)))
(apply 'command (append '("pline") coords '("c")))
(setq currobj (ssadd (entlast) currobj))
(setq coords (list 
(list 1920.5625 536.5446) 
(list 1994.585 536.3946) 
(list 1994.585 536.5716) 
(list 1920.5625 536.6216)))
(apply 'command (append '("pline") coords '("c")))
(setq currobj (ssadd (entlast) currobj))
(setq coords (list 
(list 1920.5625 536.7646) 
(list 1994.585 536.7146) 
(list 1994.585 536.8916) 
(list 1920.5625 536.8416)))
(apply 'command (append '("pline") coords '("c")))
(setq currobj (ssadd (entlast) currobj))
(setq coords (list 
(list 1920.5625 536.9846) 
(list 1994.585 537.0346) 
(list 1994.585 537.2116) 
(list 1920.5625 537.0616)))
(apply 'command (append '("pline") coords '("c")))
(setq currobj (ssadd (entlast) currobj))
(setq coords (list 
(list 1920.5625 537.2046) 
(list 1994.585 537.3546) 
(list 1994.585 537.5316) 
(list 1920.5625 537.2816)))
(apply 'command (append '("pline") coords '("c")))
(setq currobj (ssadd (entlast) currobj))
(setq coords (list 
(list 1920.5625 537.4246) 
(list 1994.585 537.6746) 
(list 1994.585 537.8516) 
(list 1920.5625 537.5016)))
(apply 'command (append '("pline") coords '("c")))
(setq currobj (ssadd (entlast) currobj))
(setq coords (list 
(list 1920.5625 537.6446) 
(list 1994.585 537.9946) 
(list 1994.585 538.1716) 
(list 1920.5625 537.7216)))
(apply 'command (append '("pline") coords '("c")))
(setq currobj (ssadd (entlast) currobj))
(setq coords (list 
(list 1920.5625 537.8646) 
(list 1994.585 538.3146) 
(list 1994.585 538.4916) 
(list 1920.5625 537.9416)))
(apply 'command (append '("pline") coords '("c")))
(setq currobj (ssadd (entlast) currobj))
(setq coords (list 
(list 1920.5625 538.0846) 
(list 1994.585 538.6346) 
(list 1994.585 538.8116) 
(list 1920.5625 538.1616)))
(apply 'command (append '("pline") coords '("c")))
(setq currobj (ssadd (entlast) currobj))
(setq coords (list 
(list 1920.5625 538.3046) 
(list 1994.585 538.9546) 
(list 1994.585 539.1316) 
(list 1920.5625 538.3816)))
(apply 'command (append '("pline") coords '("c")))
(setq currobj (ssadd (entlast) currobj))
(setq coords (list 
(list 1919.4375 538.3816) 
(list 1845.415 539.1316) 
(list 1845.415 538.9546) 
(list 1919.4375 538.3046)))
(apply 'command (append '("pline") coords '("c")))
(setq currobj (ssadd (entlast) currobj))
(setq coords (list 
(list 1919.4375 538.1616) 
(list 1845.415 538.8116) 
(list 1845.415 538.6346) 
(list 1919.4375 538.0846)))
(apply 'command (append '("pline") coords '("c")))
(setq currobj (ssadd (entlast) currobj))
(setq coords (list 
(list 1919.4375 537.9416) 
(list 1845.415 538.4916) 
(list 1845.415 538.3146) 
(list 1919.4375 537.8646)))
(apply 'command (append '("pline") coords '("c")))
(setq currobj (ssadd (entlast) currobj))
(setq coords (list 
(list 1919.4375 537.7216) 
(list 1845.415 538.1716) 
(list 1845.415 537.9946) 
(list 1919.4375 537.6446)))
(apply 'command (append '("pline") coords '("c")))
(setq currobj (ssadd (entlast) currobj))
(setq coords (list 
(list 1919.4375 537.5016) 
(list 1845.415 537.8516) 
(list 1845.415 537.6746) 
(list 1919.4375 537.4246)))
(apply 'command (append '("pline") coords '("c")))
(setq currobj (ssadd (entlast) currobj))
(setq coords (list 
(list 1919.4375 537.2816) 
(list 1845.415 537.5316) 
(list 1845.415 537.3546) 
(list 1919.4375 537.2046)))
(apply 'command (append '("pline") coords '("c")))
(setq currobj (ssadd (entlast) currobj))
(setq coords (list 
(list 1919.4375 537.0616) 
(list 1845.415 537.2116) 
(list 1845.415 537.0346) 
(list 1919.4375 536.9846)))
(apply 'command (append '("pline") coords '("c")))
(setq currobj (ssadd (entlast) currobj))
(setq coords (list 
(list 1919.4375 536.8416) 
(list 1845.415 536.8916) 
(list 1845.415 536.7146) 
(list 1919.4375 536.7646)))
(apply 'command (append '("pline") coords '("c")))
(setq currobj (ssadd (entlast) currobj))
(setq coords (list 
(list 1919.4375 536.6216) 
(list 1845.415 536.5716) 
(list 1845.415 536.3946) 
(list 1919.4375 536.5446)))
(apply 'command (append '("pline") coords '("c")))
(setq currobj (ssadd (entlast) currobj))
(setq coords (list 
(list 1919.4375 536.4016) 
(list 1845.415 536.2516) 
(list 1845.415 536.0746) 
(list 1919.4375 536.3246)))
(apply 'command (append '("pline") coords '("c")))
(setq currobj (ssadd (entlast) currobj))
(setq coords (list 
(list 1919.4375 536.1816) 
(list 1845.415 535.9316) 
(list 1845.415 535.7546) 
(list 1919.4375 536.1046)))
(apply 'command (append '("pline") coords '("c")))
(setq currobj (ssadd (entlast) currobj))
(setq coords (list 
(list 1919.4375 535.9616) 
(list 1845.415 535.6116) 
(list 1845.415 535.4346) 
(list 1919.4375 535.8846)))
(apply 'command (append '("pline") coords '("c")))
(setq currobj (ssadd (entlast) currobj))
(setq coords (list 
(list 1919.4375 535.7416) 
(list 1845.415 535.2916) 
(list 1845.415 535.1146) 
(list 1919.4375 535.6646)))
(apply 'command (append '("pline") coords '("c")))
(setq currobj (ssadd (entlast) currobj))
(setq coords (list 
(list 1919.4375 535.5216) 
(list 1845.415 534.9716) 
(list 1845.415 534.7946) 
(list 1919.4375 535.4446)))
(apply 'command (append '("pline") coords '("c")))
(setq currobj (ssadd (entlast) currobj))
(setq coords (list 
(list 1919.4375 535.3016) 
(list 1845.415 534.6516) 
(list 1845.415 534.4746) 
(list 1919.4375 535.2246)))
(apply 'command (append '("pline") coords '("c")))
(setq currobj (ssadd (entlast) currobj))
(command "_layer" "set" "nitride" "")
(command "_layer" "set" "text" "")
(command "_circle" "1919.0625,524.0816" "0.075")
(command "_circle" "1919.0625,524.3816" "0.075")
(command "_circle" "1919.0625,524.6816" "0.075")
(command "_circle" "1919.0625,524.9816" "0.075")
(command "_circle" "1919.0625,525.2816" "0.075")
(command "_circle" "1918.7625,524.0816" "0.075")
(command "_circle" "1918.7625,524.3816" "0.075")
(command "_circle" "1918.7625,524.6816" "0.075")
(command "_circle" "1918.7625,524.9816" "0.075")
(command "_circle" "1918.7625,525.2816" "0.075")
(command "_circle" "1918.4625,524.0816" "0.075")
(command "_circle" "1918.4625,524.3816" "0.075")
(command "_circle" "1918.4625,524.6816" "0.075")
(command "_circle" "1918.4625,524.9816" "0.075")
(command "_circle" "1918.4625,525.2816" "0.075")
(command "_circle" "1918.1625,524.0816" "0.075")
(command "_circle" "1918.1625,524.3816" "0.075")
(command "_circle" "1918.1625,524.6816" "0.075")
(command "_circle" "1918.1625,524.9816" "0.075")
(command "_circle" "1918.1625,525.2816" "0.075")
(command "_circle" "1917.8625,524.0816" "0.075")
(command "_circle" "1917.8625,524.3816" "0.075")
(command "_circle" "1917.8625,524.6816" "0.075")
(command "_circle" "1917.8625,524.9816" "0.075")
(command "_circle" "1917.8625,525.2816" "0.075")
(command "_layer" "set" "nitride" "")
(setq coords (list 
(list 1920.2625 549.5246) 
(list 1920.2625 665.1693) 
(list 1919.7375 665.1693) 
(list 1919.7375 549.5246)))
(apply 'command (append '("pline") coords '("c")))
(setq currobj (ssadd (entlast) currobj))
(command "_layer" "set" "prebias" "")
(command "_rectangle" "1919.7375,549.5246" "1920.2625,665.1693")
(setq currobj (ssadd (entlast) currobj))
(command "_layer" "set" "nitride" "")
(setq coords (list 
(list 1920.2625 665.1693) 
(list 1920.5625 675.1693) 
(list 1920.5625 675.1693) 
(list 1920.5625 676.1693) 
(list 1994.585 675.4193) 
(list 1994.585 680.3623) 
(list 1920.5625 679.6123) 
(list 1920.5625 680.6123) 
(list 1920.5625 680.6123) 
(list 1920.2625 690.6123) 
(list 1919.7375 690.6123) 
(list 1919.4375 680.6123) 
(list 1919.4375 680.6123) 
(list 1919.4375 679.6123) 
(list 1845.415 680.3623) 
(list 1845.415 675.4193) 
(list 1919.4375 676.1693) 
(list 1919.4375 675.1693) 
(list 1919.4375 675.1693) 
(list 1919.7375 665.1693)))
(apply 'command (append '("pline") coords '("c")))
(setq currobj (ssadd (entlast) currobj))
(command "_layer" "set" "prebias" "")
(setq coords (list 
(list 1919.4375 665.1693) 
(list 1919.4375 676.1693) 
(list 1845.415 675.4193) 
(list 1845.415 680.3623) 
(list 1919.4375 679.6123) 
(list 1919.4375 690.6123) 
(list 1920.5625 690.6123) 
(list 1920.5625 679.6123) 
(list 1994.585 680.3623) 
(list 1994.585 675.4193) 
(list 1920.5625 676.1693) 
(list 1920.5625 665.1693)))
(apply 'command (append '("pline") coords '("c")))
(setq currobj (ssadd (entlast) currobj))
(command "_layer" "set" "nitride" "")
(command "_layer" "set" "fda1" "")
(setq coords (list 
(list 1920.5625 676.3123) 
(list 1994.585 675.5623) 
(list 1994.585 675.7393) 
(list 1920.5625 676.3893)))
(apply 'command (append '("pline") coords '("c")))
(setq currobj (ssadd (entlast) currobj))
(setq coords (list 
(list 1920.5625 676.5323) 
(list 1994.585 675.8823) 
(list 1994.585 676.0593) 
(list 1920.5625 676.6093)))
(apply 'command (append '("pline") coords '("c")))
(setq currobj (ssadd (entlast) currobj))
(setq coords (list 
(list 1920.5625 676.7523) 
(list 1994.585 676.2023) 
(list 1994.585 676.3793) 
(list 1920.5625 676.8293)))
(apply 'command (append '("pline") coords '("c")))
(setq currobj (ssadd (entlast) currobj))
(setq coords (list 
(list 1920.5625 676.9723) 
(list 1994.585 676.5223) 
(list 1994.585 676.6993) 
(list 1920.5625 677.0493)))
(apply 'command (append '("pline") coords '("c")))
(setq currobj (ssadd (entlast) currobj))
(setq coords (list 
(list 1920.5625 677.1923) 
(list 1994.585 676.8423) 
(list 1994.585 677.0193) 
(list 1920.5625 677.2693)))
(apply 'command (append '("pline") coords '("c")))
(setq currobj (ssadd (entlast) currobj))
(setq coords (list 
(list 1920.5625 677.4123) 
(list 1994.585 677.1623) 
(list 1994.585 677.3393) 
(list 1920.5625 677.4893)))
(apply 'command (append '("pline") coords '("c")))
(setq currobj (ssadd (entlast) currobj))
(setq coords (list 
(list 1920.5625 677.6323) 
(list 1994.585 677.4823) 
(list 1994.585 677.6593) 
(list 1920.5625 677.7093)))
(apply 'command (append '("pline") coords '("c")))
(setq currobj (ssadd (entlast) currobj))
(setq coords (list 
(list 1920.5625 677.8523) 
(list 1994.585 677.8023) 
(list 1994.585 677.9793) 
(list 1920.5625 677.9293)))
(apply 'command (append '("pline") coords '("c")))
(setq currobj (ssadd (entlast) currobj))
(setq coords (list 
(list 1920.5625 678.0723) 
(list 1994.585 678.1223) 
(list 1994.585 678.2993) 
(list 1920.5625 678.1493)))
(apply 'command (append '("pline") coords '("c")))
(setq currobj (ssadd (entlast) currobj))
(setq coords (list 
(list 1920.5625 678.2923) 
(list 1994.585 678.4423) 
(list 1994.585 678.6193) 
(list 1920.5625 678.3693)))
(apply 'command (append '("pline") coords '("c")))
(setq currobj (ssadd (entlast) currobj))
(setq coords (list 
(list 1920.5625 678.5123) 
(list 1994.585 678.7623) 
(list 1994.585 678.9393) 
(list 1920.5625 678.5893)))
(apply 'command (append '("pline") coords '("c")))
(setq currobj (ssadd (entlast) currobj))
(setq coords (list 
(list 1920.5625 678.7323) 
(list 1994.585 679.0823) 
(list 1994.585 679.2593) 
(list 1920.5625 678.8093)))
(apply 'command (append '("pline") coords '("c")))
(setq currobj (ssadd (entlast) currobj))
(setq coords (list 
(list 1920.5625 678.9523) 
(list 1994.585 679.4023) 
(list 1994.585 679.5793) 
(list 1920.5625 679.0293)))
(apply 'command (append '("pline") coords '("c")))
(setq currobj (ssadd (entlast) currobj))
(setq coords (list 
(list 1920.5625 679.1723) 
(list 1994.585 679.7223) 
(list 1994.585 679.8993) 
(list 1920.5625 679.2493)))
(apply 'command (append '("pline") coords '("c")))
(setq currobj (ssadd (entlast) currobj))
(setq coords (list 
(list 1920.5625 679.3923) 
(list 1994.585 680.0423) 
(list 1994.585 680.2193) 
(list 1920.5625 679.4693)))
(apply 'command (append '("pline") coords '("c")))
(setq currobj (ssadd (entlast) currobj))
(setq coords (list 
(list 1919.4375 679.4693) 
(list 1845.415 680.2193) 
(list 1845.415 680.0423) 
(list 1919.4375 679.3923)))
(apply 'command (append '("pline") coords '("c")))
(setq currobj (ssadd (entlast) currobj))
(setq coords (list 
(list 1919.4375 679.2493) 
(list 1845.415 679.8993) 
(list 1845.415 679.7223) 
(list 1919.4375 679.1723)))
(apply 'command (append '("pline") coords '("c")))
(setq currobj (ssadd (entlast) currobj))
(setq coords (list 
(list 1919.4375 679.0293) 
(list 1845.415 679.5793) 
(list 1845.415 679.4023) 
(list 1919.4375 678.9523)))
(apply 'command (append '("pline") coords '("c")))
(setq currobj (ssadd (entlast) currobj))
(setq coords (list 
(list 1919.4375 678.8093) 
(list 1845.415 679.2593) 
(list 1845.415 679.0823) 
(list 1919.4375 678.7323)))
(apply 'command (append '("pline") coords '("c")))
(setq currobj (ssadd (entlast) currobj))
(setq coords (list 
(list 1919.4375 678.5893) 
(list 1845.415 678.9393) 
(list 1845.415 678.7623) 
(list 1919.4375 678.5123)))
(apply 'command (append '("pline") coords '("c")))
(setq currobj (ssadd (entlast) currobj))
(setq coords (list 
(list 1919.4375 678.3693) 
(list 1845.415 678.6193) 
(list 1845.415 678.4423) 
(list 1919.4375 678.2923)))
(apply 'command (append '("pline") coords '("c")))
(setq currobj (ssadd (entlast) currobj))
(setq coords (list 
(list 1919.4375 678.1493) 
(list 1845.415 678.2993) 
(list 1845.415 678.1223) 
(list 1919.4375 678.0723)))
(apply 'command (append '("pline") coords '("c")))
(setq currobj (ssadd (entlast) currobj))
(setq coords (list 
(list 1919.4375 677.9293) 
(list 1845.415 677.9793) 
(list 1845.415 677.8023) 
(list 1919.4375 677.8523)))
(apply 'command (append '("pline") coords '("c")))
(setq currobj (ssadd (entlast) currobj))
(setq coords (list 
(list 1919.4375 677.7093) 
(list 1845.415 677.6593) 
(list 1845.415 677.4823) 
(list 1919.4375 677.6323)))
(apply 'command (append '("pline") coords '("c")))
(setq currobj (ssadd (entlast) currobj))
(setq coords (list 
(list 1919.4375 677.4893) 
(list 1845.415 677.3393) 
(list 1845.415 677.1623) 
(list 1919.4375 677.4123)))
(apply 'command (append '("pline") coords '("c")))
(setq currobj (ssadd (entlast) currobj))
(setq coords (list 
(list 1919.4375 677.2693) 
(list 1845.415 677.0193) 
(list 1845.415 676.8423) 
(list 1919.4375 677.1923)))
(apply 'command (append '("pline") coords '("c")))
(setq currobj (ssadd (entlast) currobj))
(setq coords (list 
(list 1919.4375 677.0493) 
(list 1845.415 676.6993) 
(list 1845.415 676.5223) 
(list 1919.4375 676.9723)))
(apply 'command (append '("pline") coords '("c")))
(setq currobj (ssadd (entlast) currobj))
(setq coords (list 
(list 1919.4375 676.8293) 
(list 1845.415 676.3793) 
(list 1845.415 676.2023) 
(list 1919.4375 676.7523)))
(apply 'command (append '("pline") coords '("c")))
(setq currobj (ssadd (entlast) currobj))
(setq coords (list 
(list 1919.4375 676.6093) 
(list 1845.415 676.0593) 
(list 1845.415 675.8823) 
(list 1919.4375 676.5323)))
(apply 'command (append '("pline") coords '("c")))
(setq currobj (ssadd (entlast) currobj))
(setq coords (list 
(list 1919.4375 676.3893) 
(list 1845.415 675.7393) 
(list 1845.415 675.5623) 
(list 1919.4375 676.3123)))
(apply 'command (append '("pline") coords '("c")))
(setq currobj (ssadd (entlast) currobj))
(command "_layer" "set" "nitride" "")
(command "_layer" "set" "text" "")
(command "_circle" "1919.0625,665.1693" "0.075")
(command "_circle" "1919.0625,665.4693" "0.075")
(command "_circle" "1919.0625,665.7693" "0.075")
(command "_circle" "1919.0625,666.0693" "0.075")
(command "_circle" "1919.0625,666.3693" "0.075")
(command "_circle" "1918.7625,665.1693" "0.075")
(command "_circle" "1918.7625,665.4693" "0.075")
(command "_circle" "1918.7625,665.7693" "0.075")
(command "_circle" "1918.7625,666.0693" "0.075")
(command "_circle" "1918.7625,666.3693" "0.075")
(command "_circle" "1918.4625,665.1693" "0.075")
(command "_circle" "1918.4625,665.4693" "0.075")
(command "_circle" "1918.4625,665.7693" "0.075")
(command "_circle" "1918.4625,666.0693" "0.075")
(command "_circle" "1918.4625,666.3693" "0.075")
(command "_circle" "1918.1625,665.1693" "0.075")
(command "_circle" "1918.1625,665.4693" "0.075")
(command "_circle" "1918.1625,665.7693" "0.075")
(command "_circle" "1918.1625,666.0693" "0.075")
(command "_circle" "1918.1625,666.3693" "0.075")
(command "_circle" "1917.8625,665.1693" "0.075")
(command "_circle" "1917.8625,665.4693" "0.075")
(command "_circle" "1917.8625,665.7693" "0.075")
(command "_circle" "1917.8625,666.0693" "0.075")
(command "_circle" "1917.8625,666.3693" "0.075")
(command "_layer" "set" "nitride" "")
(setq coords (list 
(list 1920.2625 690.6123) 
(list 1920.2625 806.257) 
(list 1919.7375 806.257) 
(list 1919.7375 690.6123)))
(apply 'command (append '("pline") coords '("c")))
(setq currobj (ssadd (entlast) currobj))
(command "_layer" "set" "prebias" "")
(command "_rectangle" "1919.7375,690.6123" "1920.2625,806.257")
(setq currobj (ssadd (entlast) currobj))
(command "_layer" "set" "nitride" "")
(setq coords (list 
(list 1920.2625 806.257) 
(list 1920.5625 816.257) 
(list 1920.5625 816.257) 
(list 1920.5625 817.257) 
(list 1994.585 816.507) 
(list 1994.585 821.45) 
(list 1920.5625 820.7) 
(list 1920.5625 821.7) 
(list 1920.5625 821.7) 
(list 1920.2625 831.7) 
(list 1919.7375 831.7) 
(list 1919.4375 821.7) 
(list 1919.4375 821.7) 
(list 1919.4375 820.7) 
(list 1845.415 821.45) 
(list 1845.415 816.507) 
(list 1919.4375 817.257) 
(list 1919.4375 816.257) 
(list 1919.4375 816.257) 
(list 1919.7375 806.257)))
(apply 'command (append '("pline") coords '("c")))
(setq currobj (ssadd (entlast) currobj))
(command "_layer" "set" "prebias" "")
(setq coords (list 
(list 1919.4375 806.257) 
(list 1919.4375 817.257) 
(list 1845.415 816.507) 
(list 1845.415 821.45) 
(list 1919.4375 820.7) 
(list 1919.4375 831.7) 
(list 1920.5625 831.7) 
(list 1920.5625 820.7) 
(list 1994.585 821.45) 
(list 1994.585 816.507) 
(list 1920.5625 817.257) 
(list 1920.5625 806.257)))
(apply 'command (append '("pline") coords '("c")))
(setq currobj (ssadd (entlast) currobj))
(command "_layer" "set" "nitride" "")
(command "_layer" "set" "fda1" "")
(setq coords (list 
(list 1920.5625 817.4) 
(list 1994.585 816.65) 
(list 1994.585 816.827) 
(list 1920.5625 817.477)))
(apply 'command (append '("pline") coords '("c")))
(setq currobj (ssadd (entlast) currobj))
(setq coords (list 
(list 1920.5625 817.62) 
(list 1994.585 816.97) 
(list 1994.585 817.147) 
(list 1920.5625 817.697)))
(apply 'command (append '("pline") coords '("c")))
(setq currobj (ssadd (entlast) currobj))
(setq coords (list 
(list 1920.5625 817.84) 
(list 1994.585 817.29) 
(list 1994.585 817.467) 
(list 1920.5625 817.917)))
(apply 'command (append '("pline") coords '("c")))
(setq currobj (ssadd (entlast) currobj))
(setq coords (list 
(list 1920.5625 818.06) 
(list 1994.585 817.61) 
(list 1994.585 817.787) 
(list 1920.5625 818.137)))
(apply 'command (append '("pline") coords '("c")))
(setq currobj (ssadd (entlast) currobj))
(setq coords (list 
(list 1920.5625 818.28) 
(list 1994.585 817.93) 
(list 1994.585 818.107) 
(list 1920.5625 818.357)))
(apply 'command (append '("pline") coords '("c")))
(setq currobj (ssadd (entlast) currobj))
(setq coords (list 
(list 1920.5625 818.5) 
(list 1994.585 818.25) 
(list 1994.585 818.427) 
(list 1920.5625 818.577)))
(apply 'command (append '("pline") coords '("c")))
(setq currobj (ssadd (entlast) currobj))
(setq coords (list 
(list 1920.5625 818.72) 
(list 1994.585 818.57) 
(list 1994.585 818.747) 
(list 1920.5625 818.797)))
(apply 'command (append '("pline") coords '("c")))
(setq currobj (ssadd (entlast) currobj))
(setq coords (list 
(list 1920.5625 818.94) 
(list 1994.585 818.89) 
(list 1994.585 819.067) 
(list 1920.5625 819.017)))
(apply 'command (append '("pline") coords '("c")))
(setq currobj (ssadd (entlast) currobj))
(setq coords (list 
(list 1920.5625 819.16) 
(list 1994.585 819.21) 
(list 1994.585 819.387) 
(list 1920.5625 819.237)))
(apply 'command (append '("pline") coords '("c")))
(setq currobj (ssadd (entlast) currobj))
(setq coords (list 
(list 1920.5625 819.38) 
(list 1994.585 819.53) 
(list 1994.585 819.707) 
(list 1920.5625 819.457)))
(apply 'command (append '("pline") coords '("c")))
(setq currobj (ssadd (entlast) currobj))
(setq coords (list 
(list 1920.5625 819.6) 
(list 1994.585 819.85) 
(list 1994.585 820.027) 
(list 1920.5625 819.677)))
(apply 'command (append '("pline") coords '("c")))
(setq currobj (ssadd (entlast) currobj))
(setq coords (list 
(list 1920.5625 819.82) 
(list 1994.585 820.17) 
(list 1994.585 820.347) 
(list 1920.5625 819.897)))
(apply 'command (append '("pline") coords '("c")))
(setq currobj (ssadd (entlast) currobj))
(setq coords (list 
(list 1920.5625 820.04) 
(list 1994.585 820.49) 
(list 1994.585 820.667) 
(list 1920.5625 820.117)))
(apply 'command (append '("pline") coords '("c")))
(setq currobj (ssadd (entlast) currobj))
(setq coords (list 
(list 1920.5625 820.26) 
(list 1994.585 820.81) 
(list 1994.585 820.987) 
(list 1920.5625 820.337)))
(apply 'command (append '("pline") coords '("c")))
(setq currobj (ssadd (entlast) currobj))
(setq coords (list 
(list 1920.5625 820.48) 
(list 1994.585 821.13) 
(list 1994.585 821.307) 
(list 1920.5625 820.557)))
(apply 'command (append '("pline") coords '("c")))
(setq currobj (ssadd (entlast) currobj))
(setq coords (list 
(list 1919.4375 820.557) 
(list 1845.415 821.307) 
(list 1845.415 821.13) 
(list 1919.4375 820.48)))
(apply 'command (append '("pline") coords '("c")))
(setq currobj (ssadd (entlast) currobj))
(setq coords (list 
(list 1919.4375 820.337) 
(list 1845.415 820.987) 
(list 1845.415 820.81) 
(list 1919.4375 820.26)))
(apply 'command (append '("pline") coords '("c")))
(setq currobj (ssadd (entlast) currobj))
(setq coords (list 
(list 1919.4375 820.117) 
(list 1845.415 820.667) 
(list 1845.415 820.49) 
(list 1919.4375 820.04)))
(apply 'command (append '("pline") coords '("c")))
(setq currobj (ssadd (entlast) currobj))
(setq coords (list 
(list 1919.4375 819.897) 
(list 1845.415 820.347) 
(list 1845.415 820.17) 
(list 1919.4375 819.82)))
(apply 'command (append '("pline") coords '("c")))
(setq currobj (ssadd (entlast) currobj))
(setq coords (list 
(list 1919.4375 819.677) 
(list 1845.415 820.027) 
(list 1845.415 819.85) 
(list 1919.4375 819.6)))
(apply 'command (append '("pline") coords '("c")))
(setq currobj (ssadd (entlast) currobj))
(setq coords (list 
(list 1919.4375 819.457) 
(list 1845.415 819.707) 
(list 1845.415 819.53) 
(list 1919.4375 819.38)))
(apply 'command (append '("pline") coords '("c")))
(setq currobj (ssadd (entlast) currobj))
(setq coords (list 
(list 1919.4375 819.237) 
(list 1845.415 819.387) 
(list 1845.415 819.21) 
(list 1919.4375 819.16)))
(apply 'command (append '("pline") coords '("c")))
(setq currobj (ssadd (entlast) currobj))
(setq coords (list 
(list 1919.4375 819.017) 
(list 1845.415 819.067) 
(list 1845.415 818.89) 
(list 1919.4375 818.94)))
(apply 'command (append '("pline") coords '("c")))
(setq currobj (ssadd (entlast) currobj))
(setq coords (list 
(list 1919.4375 818.797) 
(list 1845.415 818.747) 
(list 1845.415 818.57) 
(list 1919.4375 818.72)))
(apply 'command (append '("pline") coords '("c")))
(setq currobj (ssadd (entlast) currobj))
(setq coords (list 
(list 1919.4375 818.577) 
(list 1845.415 818.427) 
(list 1845.415 818.25) 
(list 1919.4375 818.5)))
(apply 'command (append '("pline") coords '("c")))
(setq currobj (ssadd (entlast) currobj))
(setq coords (list 
(list 1919.4375 818.357) 
(list 1845.415 818.107) 
(list 1845.415 817.93) 
(list 1919.4375 818.28)))
(apply 'command (append '("pline") coords '("c")))
(setq currobj (ssadd (entlast) currobj))
(setq coords (list 
(list 1919.4375 818.137) 
(list 1845.415 817.787) 
(list 1845.415 817.61) 
(list 1919.4375 818.06)))
(apply 'command (append '("pline") coords '("c")))
(setq currobj (ssadd (entlast) currobj))
(setq coords (list 
(list 1919.4375 817.917) 
(list 1845.415 817.467) 
(list 1845.415 817.29) 
(list 1919.4375 817.84)))
(apply 'command (append '("pline") coords '("c")))
(setq currobj (ssadd (entlast) currobj))
(setq coords (list 
(list 1919.4375 817.697) 
(list 1845.415 817.147) 
(list 1845.415 816.97) 
(list 1919.4375 817.62)))
(apply 'command (append '("pline") coords '("c")))
(setq currobj (ssadd (entlast) currobj))
(setq coords (list 
(list 1919.4375 817.477) 
(list 1845.415 816.827) 
(list 1845.415 816.65) 
(list 1919.4375 817.4)))
(apply 'command (append '("pline") coords '("c")))
(setq currobj (ssadd (entlast) currobj))
(command "_layer" "set" "nitride" "")
(command "_layer" "set" "text" "")
(command "_circle" "1919.0625,806.257" "0.075")
(command "_circle" "1919.0625,806.557" "0.075")
(command "_circle" "1919.0625,806.857" "0.075")
(command "_circle" "1919.0625,807.157" "0.075")
(command "_circle" "1919.0625,807.457" "0.075")
(command "_circle" "1918.7625,806.257" "0.075")
(command "_circle" "1918.7625,806.557" "0.075")
(command "_circle" "1918.7625,806.857" "0.075")
(command "_circle" "1918.7625,807.157" "0.075")
(command "_circle" "1918.7625,807.457" "0.075")
(command "_circle" "1918.4625,806.257" "0.075")
(command "_circle" "1918.4625,806.557" "0.075")
(command "_circle" "1918.4625,806.857" "0.075")
(command "_circle" "1918.4625,807.157" "0.075")
(command "_circle" "1918.4625,807.457" "0.075")
(command "_circle" "1918.1625,806.257" "0.075")
(command "_circle" "1918.1625,806.557" "0.075")
(command "_circle" "1918.1625,806.857" "0.075")
(command "_circle" "1918.1625,807.157" "0.075")
(command "_circle" "1918.1625,807.457" "0.075")
(command "_circle" "1917.8625,806.257" "0.075")
(command "_circle" "1917.8625,806.557" "0.075")
(command "_circle" "1917.8625,806.857" "0.075")
(command "_circle" "1917.8625,807.157" "0.075")
(command "_circle" "1917.8625,807.457" "0.075")
(command "_layer" "set" "nitride" "")
(setq coords (list 
(list 1920.2625 831.7) 
(list 1920.2625 836.7) 
(list 1919.7375 836.7) 
(list 1919.7375 831.7)))
(apply 'command (append '("pline") coords '("c")))
(setq currobj (ssadd (entlast) currobj))
(command "_layer" "set" "prebias" "")
(command "_rectangle" "1919.7375,831.7" "1920.2625,836.7")
(setq currobj (ssadd (entlast) currobj))
(command "_layer" "set" "nitride" "")
(setq cooledsinglenanobeam6 currobj)
(setq currobj nil)
(setq currobj (ssadd))
; DRAWING PHOTONIC CRYSTAL
(command "_layer" "set" "negYjunc" "")
(setq coords (list 
(list 1920.135 866.7) 
(list 1920 851.7) 
(list 1920 866.7)))
(apply 'command (append '("pline") coords '("c")))
(setq currobj (ssadd (entlast) currobj))
(setq coords (list 
(list 1920.2625 836.7) 
(list 1920.415 866.7) 
(list 1921.127 866.7) 
(list 1921.127 836.7)))
(apply 'command (append '("pline") coords '("c")))
(setq currobj (ssadd (entlast) currobj))
(setq coords (list 
(list 1919.865 866.7) 
(list 1920 851.7) 
(list 1920 866.7)))
(apply 'command (append '("pline") coords '("c")))
(setq currobj (ssadd (entlast) currobj))
(setq coords (list 
(list 1919.7375 836.7) 
(list 1919.585 866.7) 
(list 1918.873 866.7) 
(list 1918.873 836.7)))
(apply 'command (append '("pline") coords '("c")))
(setq currobj (ssadd (entlast) currobj))
(command "_layer" "set" "nitride" "")
(setq yjunction6 currobj)
(setq currobj nil)
(setq currobj (ssadd))
(setq tap6 nil)
(setq tap6 (ssadd))
(command "_layer" "set" "phc" "")
(setq coords (list 
(list 1920 866.7) 
(list 1920.135 866.7) 
(list 1920.135 866.7103) 
(list 1920.135 866.7206) 
(list 1920.135 866.7308) 
(list 1920.135 866.7411) 
(list 1920.135 866.7514) 
(list 1920.135 866.7617) 
(list 1920.135 866.7719) 
(list 1920.135 866.7822) 
(list 1920.135 866.7925) 
(list 1920.135 866.8028) 
(list 1920.135 866.8131) 
(list 1920.135 866.8233) 
(list 1920.135 866.8336) 
(list 1920.135 866.8439) 
(list 1920.135 866.8542) 
(list 1920.135 866.8644) 
(list 1920.135 866.8747) 
(list 1920.135 866.885) 
(list 1920.135 866.8953) 
(list 1920.135 866.9056) 
(list 1920.135 866.9158) 
(list 1920.135 866.9261) 
(list 1920.135 866.9364) 
(list 1920.135 866.9467) 
(list 1920.135 866.9569) 
(list 1920.135 866.9672) 
(list 1920.135 866.9775) 
(list 1920.135 866.9878) 
(list 1920.135 866.9981) 
(list 1920.135 867.0083) 
(list 1920.135 867.0186) 
(list 1920.135 867.0289) 
(list 1920.135 867.0392) 
(list 1920.135 867.0494) 
(list 1920.135 867.0597) 
(list 1920.135 867.07) 
(list 1920 867.07)))
(apply 'command (append '("pline") coords '("c")))
(setq tap6 (ssadd (entlast) tap6))
(command "_mirror" (entlast) "" "1920,900" "1920,901" "No")
(setq tap6 (ssadd (entlast) tap6))
(setq coords (list 
(list 1920.4249 866.7) 
(list 1920.415 866.7) 
(list 1920.4153 866.7103) 
(list 1920.4155 866.7206) 
(list 1920.4157 866.7308) 
(list 1920.4159 866.7411) 
(list 1920.4159 866.7514) 
(list 1920.4159 866.7617) 
(list 1920.4158 866.7719) 
(list 1920.4156 866.7822) 
(list 1920.4152 866.7925) 
(list 1920.4148 866.8028) 
(list 1920.4143 866.8131) 
(list 1920.4138 866.8233) 
(list 1920.4133 866.8336) 
(list 1920.4127 866.8439) 
(list 1920.4122 866.8542) 
(list 1920.4117 866.8644) 
(list 1920.4113 866.8747) 
(list 1920.411 866.885) 
(list 1920.4108 866.8953) 
(list 1920.4108 866.9056) 
(list 1920.411 866.9158) 
(list 1920.4114 866.9261) 
(list 1920.4119 866.9364) 
(list 1920.4126 866.9467) 
(list 1920.4135 866.9569) 
(list 1920.4145 866.9672) 
(list 1920.4157 866.9775) 
(list 1920.4169 866.9878) 
(list 1920.4182 866.9981) 
(list 1920.4195 867.0083) 
(list 1920.4208 867.0186) 
(list 1920.4219 867.0289) 
(list 1920.423 867.0392) 
(list 1920.4238 867.0494) 
(list 1920.4245 867.0597) 
(list 1920.4249 867.07) 
(list 1920.4249 867.07)))
(apply 'command (append '("pline") coords '("c")))
(setq tap6 (ssadd (entlast) tap6))
(command "_mirror" (entlast) "" "1920,900" "1920,901" "No")
(setq tap6 (ssadd (entlast) tap6))
(setq coords (list 
(list 1921.127 866.7) 
(list 1920.4249 866.7) 
(list 1920.4249 866.7103) 
(list 1920.4249 866.7206) 
(list 1920.4249 866.7308) 
(list 1920.4249 866.7411) 
(list 1920.4249 866.7514) 
(list 1920.4249 866.7617) 
(list 1920.4249 866.7719) 
(list 1920.4249 866.7822) 
(list 1920.4249 866.7925) 
(list 1920.4249 866.8028) 
(list 1920.4249 866.8131) 
(list 1920.4249 866.8233) 
(list 1920.4249 866.8336) 
(list 1920.4249 866.8439) 
(list 1920.4249 866.8542) 
(list 1920.4249 866.8644) 
(list 1920.4249 866.8747) 
(list 1920.4249 866.885) 
(list 1920.4249 866.8953) 
(list 1920.4249 866.9056) 
(list 1920.4249 866.9158) 
(list 1920.4249 866.9261) 
(list 1920.4249 866.9364) 
(list 1920.4249 866.9467) 
(list 1920.4249 866.9569) 
(list 1920.4249 866.9672) 
(list 1920.4249 866.9775) 
(list 1920.4249 866.9878) 
(list 1920.4249 866.9981) 
(list 1920.4249 867.0083) 
(list 1920.4249 867.0186) 
(list 1920.4249 867.0289) 
(list 1920.4249 867.0392) 
(list 1920.4249 867.0494) 
(list 1920.4249 867.0597) 
(list 1920.4249 867.07) 
(list 1921.127 867.07)))
(apply 'command (append '("pline") coords '("c")))
(setq tap6 (ssadd (entlast) tap6))
(command "_mirror" (entlast) "" "1920,900" "1920,901" "No")
(setq tap6 (ssadd (entlast) tap6))
(setq coords (list 
(list 1920 867.07) 
(list 1920.135 867.07) 
(list 1920.135 867.0803) 
(list 1920.135 867.0906) 
(list 1920.135 867.1008) 
(list 1920.135 867.1111) 
(list 1920.135 867.1214) 
(list 1920.135 867.1317) 
(list 1920.135 867.1419) 
(list 1920.135 867.1522) 
(list 1920.135 867.1625) 
(list 1920.135 867.1728) 
(list 1920.135 867.1831) 
(list 1920.135 867.1933) 
(list 1920.135 867.2036) 
(list 1920.135 867.2139) 
(list 1920.135 867.2242) 
(list 1920.135 867.2344) 
(list 1920.135 867.2447) 
(list 1920.135 867.255) 
(list 1920.135 867.2653) 
(list 1920.135 867.2756) 
(list 1920.135 867.2858) 
(list 1920.135 867.2961) 
(list 1920.135 867.3064) 
(list 1920.135 867.3167) 
(list 1920.135 867.3269) 
(list 1920.135 867.3372) 
(list 1920.135 867.3475) 
(list 1920.135 867.3578) 
(list 1920.135 867.3681) 
(list 1920.135 867.3783) 
(list 1920.135 867.3886) 
(list 1920.135 867.3989) 
(list 1920.135 867.4092) 
(list 1920.135 867.4194) 
(list 1920.135 867.4297) 
(list 1920.135 867.44) 
(list 1920 867.44)))
(apply 'command (append '("pline") coords '("c")))
(setq tap6 (ssadd (entlast) tap6))
(command "_mirror" (entlast) "" "1920,900" "1920,901" "No")
(setq tap6 (ssadd (entlast) tap6))
(setq coords (list 
(list 1920.4348 867.07) 
(list 1920.4249 867.07) 
(list 1920.425 867.0803) 
(list 1920.4249 867.0906) 
(list 1920.4244 867.1008) 
(list 1920.4237 867.1111) 
(list 1920.4226 867.1214) 
(list 1920.4213 867.1317) 
(list 1920.4198 867.1419) 
(list 1920.418 867.1522) 
(list 1920.4162 867.1625) 
(list 1920.4142 867.1728) 
(list 1920.4122 867.1831) 
(list 1920.4103 867.1933) 
(list 1920.4084 867.2036) 
(list 1920.4068 867.2139) 
(list 1920.4053 867.2242) 
(list 1920.4042 867.2344) 
(list 1920.4034 867.2447) 
(list 1920.4029 867.255) 
(list 1920.4029 867.2653) 
(list 1920.4033 867.2756) 
(list 1920.4042 867.2858) 
(list 1920.4054 867.2961) 
(list 1920.4071 867.3064) 
(list 1920.4091 867.3167) 
(list 1920.4114 867.3269) 
(list 1920.4139 867.3372) 
(list 1920.4166 867.3475) 
(list 1920.4194 867.3578) 
(list 1920.4222 867.3681) 
(list 1920.4249 867.3783) 
(list 1920.4275 867.3886) 
(list 1920.4297 867.3989) 
(list 1920.4317 867.4092) 
(list 1920.4332 867.4194) 
(list 1920.4343 867.4297) 
(list 1920.4348 867.44) 
(list 1920.4348 867.44)))
(apply 'command (append '("pline") coords '("c")))
(setq tap6 (ssadd (entlast) tap6))
(command "_mirror" (entlast) "" "1920,900" "1920,901" "No")
(setq tap6 (ssadd (entlast) tap6))
(setq coords (list 
(list 1921.127 867.07) 
(list 1920.4348 867.07) 
(list 1920.4348 867.0803) 
(list 1920.4348 867.0906) 
(list 1920.4348 867.1008) 
(list 1920.4348 867.1111) 
(list 1920.4348 867.1214) 
(list 1920.4348 867.1317) 
(list 1920.4348 867.1419) 
(list 1920.4348 867.1522) 
(list 1920.4348 867.1625) 
(list 1920.4348 867.1728) 
(list 1920.4348 867.1831) 
(list 1920.4348 867.1933) 
(list 1920.4348 867.2036) 
(list 1920.4348 867.2139) 
(list 1920.4348 867.2242) 
(list 1920.4348 867.2344) 
(list 1920.4348 867.2447) 
(list 1920.4348 867.255) 
(list 1920.4348 867.2653) 
(list 1920.4348 867.2756) 
(list 1920.4348 867.2858) 
(list 1920.4348 867.2961) 
(list 1920.4348 867.3064) 
(list 1920.4348 867.3167) 
(list 1920.4348 867.3269) 
(list 1920.4348 867.3372) 
(list 1920.4348 867.3475) 
(list 1920.4348 867.3578) 
(list 1920.4348 867.3681) 
(list 1920.4348 867.3783) 
(list 1920.4348 867.3886) 
(list 1920.4348 867.3989) 
(list 1920.4348 867.4092) 
(list 1920.4348 867.4194) 
(list 1920.4348 867.4297) 
(list 1920.4348 867.44) 
(list 1921.127 867.44)))
(apply 'command (append '("pline") coords '("c")))
(setq tap6 (ssadd (entlast) tap6))
(command "_mirror" (entlast) "" "1920,900" "1920,901" "No")
(setq tap6 (ssadd (entlast) tap6))
(setq coords (list 
(list 1920 867.44) 
(list 1920.135 867.44) 
(list 1920.135 867.4503) 
(list 1920.135 867.4606) 
(list 1920.135 867.4708) 
(list 1920.135 867.4811) 
(list 1920.135 867.4914) 
(list 1920.135 867.5017) 
(list 1920.135 867.5119) 
(list 1920.135 867.5222) 
(list 1920.135 867.5325) 
(list 1920.135 867.5428) 
(list 1920.135 867.5531) 
(list 1920.135 867.5633) 
(list 1920.135 867.5736) 
(list 1920.135 867.5839) 
(list 1920.135 867.5942) 
(list 1920.135 867.6044) 
(list 1920.135 867.6147) 
(list 1920.135 867.625) 
(list 1920.135 867.6353) 
(list 1920.135 867.6456) 
(list 1920.135 867.6558) 
(list 1920.135 867.6661) 
(list 1920.135 867.6764) 
(list 1920.135 867.6867) 
(list 1920.135 867.6969) 
(list 1920.135 867.7072) 
(list 1920.135 867.7175) 
(list 1920.135 867.7278) 
(list 1920.135 867.7381) 
(list 1920.135 867.7483) 
(list 1920.135 867.7586) 
(list 1920.135 867.7689) 
(list 1920.135 867.7792) 
(list 1920.135 867.7894) 
(list 1920.135 867.7997) 
(list 1920.135 867.81) 
(list 1920 867.81)))
(apply 'command (append '("pline") coords '("c")))
(setq tap6 (ssadd (entlast) tap6))
(command "_mirror" (entlast) "" "1920,900" "1920,901" "No")
(setq tap6 (ssadd (entlast) tap6))
(setq coords (list 
(list 1920.4447 867.44) 
(list 1920.4348 867.44) 
(list 1920.4348 867.4503) 
(list 1920.4342 867.4606) 
(list 1920.4331 867.4708) 
(list 1920.4315 867.4811) 
(list 1920.4293 867.4914) 
(list 1920.4267 867.5017) 
(list 1920.4238 867.5119) 
(list 1920.4205 867.5222) 
(list 1920.4171 867.5325) 
(list 1920.4136 867.5428) 
(list 1920.4101 867.5531) 
(list 1920.4067 867.5633) 
(list 1920.4036 867.5736) 
(list 1920.4008 867.5839) 
(list 1920.3985 867.5942) 
(list 1920.3967 867.6044) 
(list 1920.3955 867.6147) 
(list 1920.3949 867.625) 
(list 1920.395 867.6353) 
(list 1920.3959 867.6456) 
(list 1920.3974 867.6558) 
(list 1920.3995 867.6661) 
(list 1920.4023 867.6764) 
(list 1920.4055 867.6867) 
(list 1920.4093 867.6969) 
(list 1920.4133 867.7072) 
(list 1920.4176 867.7175) 
(list 1920.4219 867.7278) 
(list 1920.4262 867.7381) 
(list 1920.4303 867.7483) 
(list 1920.4342 867.7586) 
(list 1920.4375 867.7689) 
(list 1920.4404 867.7792) 
(list 1920.4426 867.7894) 
(list 1920.444 867.7997) 
(list 1920.4447 867.81) 
(list 1920.4447 867.81)))
(apply 'command (append '("pline") coords '("c")))
(setq tap6 (ssadd (entlast) tap6))
(command "_mirror" (entlast) "" "1920,900" "1920,901" "No")
(setq tap6 (ssadd (entlast) tap6))
(setq coords (list 
(list 1921.127 867.44) 
(list 1920.4447 867.44) 
(list 1920.4447 867.4503) 
(list 1920.4447 867.4606) 
(list 1920.4447 867.4708) 
(list 1920.4447 867.4811) 
(list 1920.4447 867.4914) 
(list 1920.4447 867.5017) 
(list 1920.4447 867.5119) 
(list 1920.4447 867.5222) 
(list 1920.4447 867.5325) 
(list 1920.4447 867.5428) 
(list 1920.4447 867.5531) 
(list 1920.4447 867.5633) 
(list 1920.4447 867.5736) 
(list 1920.4447 867.5839) 
(list 1920.4447 867.5942) 
(list 1920.4447 867.6044) 
(list 1920.4447 867.6147) 
(list 1920.4447 867.625) 
(list 1920.4447 867.6353) 
(list 1920.4447 867.6456) 
(list 1920.4447 867.6558) 
(list 1920.4447 867.6661) 
(list 1920.4447 867.6764) 
(list 1920.4447 867.6867) 
(list 1920.4447 867.6969) 
(list 1920.4447 867.7072) 
(list 1920.4447 867.7175) 
(list 1920.4447 867.7278) 
(list 1920.4447 867.7381) 
(list 1920.4447 867.7483) 
(list 1920.4447 867.7586) 
(list 1920.4447 867.7689) 
(list 1920.4447 867.7792) 
(list 1920.4447 867.7894) 
(list 1920.4447 867.7997) 
(list 1920.4447 867.81) 
(list 1921.127 867.81)))
(apply 'command (append '("pline") coords '("c")))
(setq tap6 (ssadd (entlast) tap6))
(command "_mirror" (entlast) "" "1920,900" "1920,901" "No")
(setq tap6 (ssadd (entlast) tap6))
(setq coords (list 
(list 1920 867.81) 
(list 1920.135 867.81) 
(list 1920.135 867.8203) 
(list 1920.135 867.8306) 
(list 1920.135 867.8408) 
(list 1920.135 867.8511) 
(list 1920.135 867.8614) 
(list 1920.135 867.8717) 
(list 1920.135 867.8819) 
(list 1920.135 867.8922) 
(list 1920.135 867.9025) 
(list 1920.135 867.9128) 
(list 1920.135 867.9231) 
(list 1920.135 867.9333) 
(list 1920.135 867.9436) 
(list 1920.135 867.9539) 
(list 1920.135 867.9642) 
(list 1920.135 867.9744) 
(list 1920.135 867.9847) 
(list 1920.135 867.995) 
(list 1920.135 868.0053) 
(list 1920.135 868.0156) 
(list 1920.135 868.0258) 
(list 1920.135 868.0361) 
(list 1920.135 868.0464) 
(list 1920.135 868.0567) 
(list 1920.135 868.0669) 
(list 1920.135 868.0772) 
(list 1920.135 868.0875) 
(list 1920.135 868.0978) 
(list 1920.135 868.1081) 
(list 1920.135 868.1183) 
(list 1920.135 868.1286) 
(list 1920.135 868.1389) 
(list 1920.135 868.1492) 
(list 1920.135 868.1594) 
(list 1920.135 868.1697) 
(list 1920.135 868.18) 
(list 1920 868.18)))
(apply 'command (append '("pline") coords '("c")))
(setq tap6 (ssadd (entlast) tap6))
(command "_mirror" (entlast) "" "1920,900" "1920,901" "No")
(setq tap6 (ssadd (entlast) tap6))
(setq coords (list 
(list 1920.4546 867.81) 
(list 1920.4447 867.81) 
(list 1920.4446 867.8203) 
(list 1920.4436 867.8306) 
(list 1920.4418 867.8408) 
(list 1920.4393 867.8511) 
(list 1920.436 867.8614) 
(list 1920.4322 867.8717) 
(list 1920.4278 867.8819) 
(list 1920.423 867.8922) 
(list 1920.418 867.9025) 
(list 1920.413 867.9128) 
(list 1920.4079 867.9231) 
(list 1920.4032 867.9333) 
(list 1920.3988 867.9436) 
(list 1920.3949 867.9539) 
(list 1920.3917 867.9642) 
(list 1920.3892 867.9744) 
(list 1920.3876 867.9847) 
(list 1920.3869 867.995) 
(list 1920.3871 868.0053) 
(list 1920.3884 868.0156) 
(list 1920.3905 868.0258) 
(list 1920.3936 868.0361) 
(list 1920.3974 868.0464) 
(list 1920.402 868.0567) 
(list 1920.4071 868.0669) 
(list 1920.4127 868.0772) 
(list 1920.4185 868.0875) 
(list 1920.4244 868.0978) 
(list 1920.4302 868.1081) 
(list 1920.4358 868.1183) 
(list 1920.4409 868.1286) 
(list 1920.4453 868.1389) 
(list 1920.4491 868.1492) 
(list 1920.4519 868.1594) 
(list 1920.4538 868.1697) 
(list 1920.4546 868.18) 
(list 1920.4546 868.18)))
(apply 'command (append '("pline") coords '("c")))
(setq tap6 (ssadd (entlast) tap6))
(command "_mirror" (entlast) "" "1920,900" "1920,901" "No")
(setq tap6 (ssadd (entlast) tap6))
(setq coords (list 
(list 1921.127 867.81) 
(list 1920.4546 867.81) 
(list 1920.4546 867.8203) 
(list 1920.4546 867.8306) 
(list 1920.4546 867.8408) 
(list 1920.4546 867.8511) 
(list 1920.4546 867.8614) 
(list 1920.4546 867.8717) 
(list 1920.4546 867.8819) 
(list 1920.4546 867.8922) 
(list 1920.4546 867.9025) 
(list 1920.4546 867.9128) 
(list 1920.4546 867.9231) 
(list 1920.4546 867.9333) 
(list 1920.4546 867.9436) 
(list 1920.4546 867.9539) 
(list 1920.4546 867.9642) 
(list 1920.4546 867.9744) 
(list 1920.4546 867.9847) 
(list 1920.4546 867.995) 
(list 1920.4546 868.0053) 
(list 1920.4546 868.0156) 
(list 1920.4546 868.0258) 
(list 1920.4546 868.0361) 
(list 1920.4546 868.0464) 
(list 1920.4546 868.0567) 
(list 1920.4546 868.0669) 
(list 1920.4546 868.0772) 
(list 1920.4546 868.0875) 
(list 1920.4546 868.0978) 
(list 1920.4546 868.1081) 
(list 1920.4546 868.1183) 
(list 1920.4546 868.1286) 
(list 1920.4546 868.1389) 
(list 1920.4546 868.1492) 
(list 1920.4546 868.1594) 
(list 1920.4546 868.1697) 
(list 1920.4546 868.18) 
(list 1921.127 868.18)))
(apply 'command (append '("pline") coords '("c")))
(setq tap6 (ssadd (entlast) tap6))
(command "_mirror" (entlast) "" "1920,900" "1920,901" "No")
(setq tap6 (ssadd (entlast) tap6))
(setq coords (list 
(list 1920 868.18) 
(list 1920.135 868.18) 
(list 1920.135 868.1903) 
(list 1920.135 868.2006) 
(list 1920.135 868.2108) 
(list 1920.135 868.2211) 
(list 1920.135 868.2314) 
(list 1920.135 868.2417) 
(list 1920.135 868.2519) 
(list 1920.135 868.2622) 
(list 1920.135 868.2725) 
(list 1920.135 868.2828) 
(list 1920.135 868.2931) 
(list 1920.135 868.3033) 
(list 1920.135 868.3136) 
(list 1920.135 868.3239) 
(list 1920.135 868.3342) 
(list 1920.135 868.3444) 
(list 1920.135 868.3547) 
(list 1920.135 868.365) 
(list 1920.135 868.3753) 
(list 1920.135 868.3856) 
(list 1920.135 868.3958) 
(list 1920.135 868.4061) 
(list 1920.135 868.4164) 
(list 1920.135 868.4267) 
(list 1920.135 868.4369) 
(list 1920.135 868.4472) 
(list 1920.135 868.4575) 
(list 1920.135 868.4678) 
(list 1920.135 868.4781) 
(list 1920.135 868.4883) 
(list 1920.135 868.4986) 
(list 1920.135 868.5089) 
(list 1920.135 868.5192) 
(list 1920.135 868.5294) 
(list 1920.135 868.5397) 
(list 1920.135 868.55) 
(list 1920 868.55)))
(apply 'command (append '("pline") coords '("c")))
(setq tap6 (ssadd (entlast) tap6))
(command "_mirror" (entlast) "" "1920,900" "1920,901" "No")
(setq tap6 (ssadd (entlast) tap6))
(setq coords (list 
(list 1920.4645 868.18) 
(list 1920.4546 868.18) 
(list 1920.4543 868.1903) 
(list 1920.453 868.2006) 
(list 1920.4505 868.2108) 
(list 1920.4471 868.2211) 
(list 1920.4427 868.2314) 
(list 1920.4376 868.2417) 
(list 1920.4318 868.2519) 
(list 1920.4255 868.2622) 
(list 1920.419 868.2725) 
(list 1920.4123 868.2828) 
(list 1920.4058 868.2931) 
(list 1920.3996 868.3033) 
(list 1920.3939 868.3136) 
(list 1920.3889 868.3239) 
(list 1920.3848 868.3342) 
(list 1920.3817 868.3444) 
(list 1920.3797 868.3547) 
(list 1920.3789 868.365) 
(list 1920.3792 868.3753) 
(list 1920.3809 868.3856) 
(list 1920.3837 868.3958) 
(list 1920.3876 868.4061) 
(list 1920.3926 868.4164) 
(list 1920.3984 868.4267) 
(list 1920.405 868.4369) 
(list 1920.4121 868.4472) 
(list 1920.4194 868.4575) 
(list 1920.4269 868.4678) 
(list 1920.4342 868.4781) 
(list 1920.4412 868.4883) 
(list 1920.4476 868.4986) 
(list 1920.4531 868.5089) 
(list 1920.4578 868.5192) 
(list 1920.4613 868.5294) 
(list 1920.4635 868.5397) 
(list 1920.4645 868.55) 
(list 1920.4645 868.55)))
(apply 'command (append '("pline") coords '("c")))
(setq tap6 (ssadd (entlast) tap6))
(command "_mirror" (entlast) "" "1920,900" "1920,901" "No")
(setq tap6 (ssadd (entlast) tap6))
(setq coords (list 
(list 1921.127 868.18) 
(list 1920.4645 868.18) 
(list 1920.4645 868.1903) 
(list 1920.4645 868.2006) 
(list 1920.4645 868.2108) 
(list 1920.4645 868.2211) 
(list 1920.4645 868.2314) 
(list 1920.4645 868.2417) 
(list 1920.4645 868.2519) 
(list 1920.4645 868.2622) 
(list 1920.4645 868.2725) 
(list 1920.4645 868.2828) 
(list 1920.4645 868.2931) 
(list 1920.4645 868.3033) 
(list 1920.4645 868.3136) 
(list 1920.4645 868.3239) 
(list 1920.4645 868.3342) 
(list 1920.4645 868.3444) 
(list 1920.4645 868.3547) 
(list 1920.4645 868.365) 
(list 1920.4645 868.3753) 
(list 1920.4645 868.3856) 
(list 1920.4645 868.3958) 
(list 1920.4645 868.4061) 
(list 1920.4645 868.4164) 
(list 1920.4645 868.4267) 
(list 1920.4645 868.4369) 
(list 1920.4645 868.4472) 
(list 1920.4645 868.4575) 
(list 1920.4645 868.4678) 
(list 1920.4645 868.4781) 
(list 1920.4645 868.4883) 
(list 1920.4645 868.4986) 
(list 1920.4645 868.5089) 
(list 1920.4645 868.5192) 
(list 1920.4645 868.5294) 
(list 1920.4645 868.5397) 
(list 1920.4645 868.55) 
(list 1921.127 868.55)))
(apply 'command (append '("pline") coords '("c")))
(setq tap6 (ssadd (entlast) tap6))
(command "_mirror" (entlast) "" "1920,900" "1920,901" "No")
(setq tap6 (ssadd (entlast) tap6))
(setq coords (list 
(list 1920 868.55) 
(list 1920.135 868.55) 
(list 1920.135 868.5603) 
(list 1920.135 868.5706) 
(list 1920.135 868.5808) 
(list 1920.135 868.5911) 
(list 1920.135 868.6014) 
(list 1920.135 868.6117) 
(list 1920.135 868.6219) 
(list 1920.135 868.6322) 
(list 1920.135 868.6425) 
(list 1920.135 868.6528) 
(list 1920.135 868.6631) 
(list 1920.135 868.6733) 
(list 1920.135 868.6836) 
(list 1920.135 868.6939) 
(list 1920.135 868.7042) 
(list 1920.135 868.7144) 
(list 1920.135 868.7247) 
(list 1920.135 868.735) 
(list 1920.135 868.7453) 
(list 1920.135 868.7556) 
(list 1920.135 868.7658) 
(list 1920.135 868.7761) 
(list 1920.135 868.7864) 
(list 1920.135 868.7967) 
(list 1920.135 868.8069) 
(list 1920.135 868.8172) 
(list 1920.135 868.8275) 
(list 1920.135 868.8378) 
(list 1920.135 868.8481) 
(list 1920.135 868.8583) 
(list 1920.135 868.8686) 
(list 1920.135 868.8789) 
(list 1920.135 868.8892) 
(list 1920.135 868.8994) 
(list 1920.135 868.9097) 
(list 1920.135 868.92) 
(list 1920 868.92)))
(apply 'command (append '("pline") coords '("c")))
(setq tap6 (ssadd (entlast) tap6))
(command "_mirror" (entlast) "" "1920,900" "1920,901" "No")
(setq tap6 (ssadd (entlast) tap6))
(setq coords (list 
(list 1920.4744 868.55) 
(list 1920.4645 868.55) 
(list 1920.4641 868.5603) 
(list 1920.4623 868.5706) 
(list 1920.4592 868.5808) 
(list 1920.4549 868.5911) 
(list 1920.4494 868.6014) 
(list 1920.443 868.6117) 
(list 1920.4358 868.6219) 
(list 1920.428 868.6322) 
(list 1920.4199 868.6425) 
(list 1920.4117 868.6528) 
(list 1920.4037 868.6631) 
(list 1920.3961 868.6733) 
(list 1920.3891 868.6836) 
(list 1920.383 868.6939) 
(list 1920.378 868.7042) 
(list 1920.3742 868.7144) 
(list 1920.3718 868.7247) 
(list 1920.3708 868.735) 
(list 1920.3713 868.7453) 
(list 1920.3734 868.7556) 
(list 1920.3769 868.7658) 
(list 1920.3817 868.7761) 
(list 1920.3878 868.7864) 
(list 1920.3949 868.7967) 
(list 1920.4029 868.8069) 
(list 1920.4114 868.8172) 
(list 1920.4204 868.8275) 
(list 1920.4294 868.8378) 
(list 1920.4382 868.8481) 
(list 1920.4466 868.8583) 
(list 1920.4543 868.8686) 
(list 1920.4609 868.8789) 
(list 1920.4665 868.8892) 
(list 1920.4706 868.8994) 
(list 1920.4733 868.9097) 
(list 1920.4744 868.92) 
(list 1920.4744 868.92)))
(apply 'command (append '("pline") coords '("c")))
(setq tap6 (ssadd (entlast) tap6))
(command "_mirror" (entlast) "" "1920,900" "1920,901" "No")
(setq tap6 (ssadd (entlast) tap6))
(setq coords (list 
(list 1921.127 868.55) 
(list 1920.4744 868.55) 
(list 1920.4744 868.5603) 
(list 1920.4744 868.5706) 
(list 1920.4744 868.5808) 
(list 1920.4744 868.5911) 
(list 1920.4744 868.6014) 
(list 1920.4744 868.6117) 
(list 1920.4744 868.6219) 
(list 1920.4744 868.6322) 
(list 1920.4744 868.6425) 
(list 1920.4744 868.6528) 
(list 1920.4744 868.6631) 
(list 1920.4744 868.6733) 
(list 1920.4744 868.6836) 
(list 1920.4744 868.6939) 
(list 1920.4744 868.7042) 
(list 1920.4744 868.7144) 
(list 1920.4744 868.7247) 
(list 1920.4744 868.735) 
(list 1920.4744 868.7453) 
(list 1920.4744 868.7556) 
(list 1920.4744 868.7658) 
(list 1920.4744 868.7761) 
(list 1920.4744 868.7864) 
(list 1920.4744 868.7967) 
(list 1920.4744 868.8069) 
(list 1920.4744 868.8172) 
(list 1920.4744 868.8275) 
(list 1920.4744 868.8378) 
(list 1920.4744 868.8481) 
(list 1920.4744 868.8583) 
(list 1920.4744 868.8686) 
(list 1920.4744 868.8789) 
(list 1920.4744 868.8892) 
(list 1920.4744 868.8994) 
(list 1920.4744 868.9097) 
(list 1920.4744 868.92) 
(list 1921.127 868.92)))
(apply 'command (append '("pline") coords '("c")))
(setq tap6 (ssadd (entlast) tap6))
(command "_mirror" (entlast) "" "1920,900" "1920,901" "No")
(setq tap6 (ssadd (entlast) tap6))
(setq coords (list 
(list 1920 868.92) 
(list 1920.135 868.92) 
(list 1920.135 868.9303) 
(list 1920.135 868.9406) 
(list 1920.135 868.9508) 
(list 1920.135 868.9611) 
(list 1920.135 868.9714) 
(list 1920.135 868.9817) 
(list 1920.135 868.9919) 
(list 1920.135 869.0022) 
(list 1920.135 869.0125) 
(list 1920.135 869.0228) 
(list 1920.135 869.0331) 
(list 1920.135 869.0433) 
(list 1920.135 869.0536) 
(list 1920.135 869.0639) 
(list 1920.135 869.0742) 
(list 1920.135 869.0844) 
(list 1920.135 869.0947) 
(list 1920.135 869.105) 
(list 1920.135 869.1153) 
(list 1920.135 869.1256) 
(list 1920.135 869.1358) 
(list 1920.135 869.1461) 
(list 1920.135 869.1564) 
(list 1920.135 869.1667) 
(list 1920.135 869.1769) 
(list 1920.135 869.1872) 
(list 1920.135 869.1975) 
(list 1920.135 869.2078) 
(list 1920.135 869.2181) 
(list 1920.135 869.2283) 
(list 1920.135 869.2386) 
(list 1920.135 869.2489) 
(list 1920.135 869.2592) 
(list 1920.135 869.2694) 
(list 1920.135 869.2797) 
(list 1920.135 869.29) 
(list 1920 869.29)))
(apply 'command (append '("pline") coords '("c")))
(setq tap6 (ssadd (entlast) tap6))
(command "_mirror" (entlast) "" "1920,900" "1920,901" "No")
(setq tap6 (ssadd (entlast) tap6))
(setq coords (list 
(list 1920.4843 868.92) 
(list 1920.4744 868.92) 
(list 1920.4739 868.9303) 
(list 1920.4717 868.9406) 
(list 1920.4679 868.9508) 
(list 1920.4627 868.9611) 
(list 1920.4561 868.9714) 
(list 1920.4484 868.9817) 
(list 1920.4398 868.9919) 
(list 1920.4305 869.0022) 
(list 1920.4208 869.0125) 
(list 1920.4111 869.0228) 
(list 1920.4015 869.0331) 
(list 1920.3925 869.0433) 
(list 1920.3843 869.0536) 
(list 1920.3771 869.0639) 
(list 1920.3712 869.0742) 
(list 1920.3667 869.0844) 
(list 1920.3639 869.0947) 
(list 1920.3628 869.105) 
(list 1920.3634 869.1153) 
(list 1920.3659 869.1256) 
(list 1920.37 869.1358) 
(list 1920.3758 869.1461) 
(list 1920.3829 869.1564) 
(list 1920.3913 869.1667) 
(list 1920.4007 869.1769) 
(list 1920.4108 869.1872) 
(list 1920.4213 869.1975) 
(list 1920.4319 869.2078) 
(list 1920.4422 869.2181) 
(list 1920.452 869.2283) 
(list 1920.4609 869.2386) 
(list 1920.4687 869.2489) 
(list 1920.4752 869.2592) 
(list 1920.48 869.2694) 
(list 1920.4831 869.2797) 
(list 1920.4843 869.29) 
(list 1920.4843 869.29)))
(apply 'command (append '("pline") coords '("c")))
(setq tap6 (ssadd (entlast) tap6))
(command "_mirror" (entlast) "" "1920,900" "1920,901" "No")
(setq tap6 (ssadd (entlast) tap6))
(setq coords (list 
(list 1921.127 868.92) 
(list 1920.4843 868.92) 
(list 1920.4843 868.9303) 
(list 1920.4843 868.9406) 
(list 1920.4843 868.9508) 
(list 1920.4843 868.9611) 
(list 1920.4843 868.9714) 
(list 1920.4843 868.9817) 
(list 1920.4843 868.9919) 
(list 1920.4843 869.0022) 
(list 1920.4843 869.0125) 
(list 1920.4843 869.0228) 
(list 1920.4843 869.0331) 
(list 1920.4843 869.0433) 
(list 1920.4843 869.0536) 
(list 1920.4843 869.0639) 
(list 1920.4843 869.0742) 
(list 1920.4843 869.0844) 
(list 1920.4843 869.0947) 
(list 1920.4843 869.105) 
(list 1920.4843 869.1153) 
(list 1920.4843 869.1256) 
(list 1920.4843 869.1358) 
(list 1920.4843 869.1461) 
(list 1920.4843 869.1564) 
(list 1920.4843 869.1667) 
(list 1920.4843 869.1769) 
(list 1920.4843 869.1872) 
(list 1920.4843 869.1975) 
(list 1920.4843 869.2078) 
(list 1920.4843 869.2181) 
(list 1920.4843 869.2283) 
(list 1920.4843 869.2386) 
(list 1920.4843 869.2489) 
(list 1920.4843 869.2592) 
(list 1920.4843 869.2694) 
(list 1920.4843 869.2797) 
(list 1920.4843 869.29) 
(list 1921.127 869.29)))
(apply 'command (append '("pline") coords '("c")))
(setq tap6 (ssadd (entlast) tap6))
(command "_mirror" (entlast) "" "1920,900" "1920,901" "No")
(setq tap6 (ssadd (entlast) tap6))
(setq coords (list 
(list 1920 869.29) 
(list 1920.135 869.29) 
(list 1920.135 869.3003) 
(list 1920.135 869.3106) 
(list 1920.135 869.3208) 
(list 1920.135 869.3311) 
(list 1920.135 869.3414) 
(list 1920.135 869.3517) 
(list 1920.135 869.3619) 
(list 1920.135 869.3722) 
(list 1920.135 869.3825) 
(list 1920.135 869.3928) 
(list 1920.135 869.4031) 
(list 1920.135 869.4133) 
(list 1920.135 869.4236) 
(list 1920.135 869.4339) 
(list 1920.135 869.4442) 
(list 1920.135 869.4544) 
(list 1920.135 869.4647) 
(list 1920.135 869.475) 
(list 1920.135 869.4853) 
(list 1920.135 869.4956) 
(list 1920.135 869.5058) 
(list 1920.135 869.5161) 
(list 1920.135 869.5264) 
(list 1920.135 869.5367) 
(list 1920.135 869.5469) 
(list 1920.135 869.5572) 
(list 1920.135 869.5675) 
(list 1920.135 869.5778) 
(list 1920.135 869.5881) 
(list 1920.135 869.5983) 
(list 1920.135 869.6086) 
(list 1920.135 869.6189) 
(list 1920.135 869.6292) 
(list 1920.135 869.6394) 
(list 1920.135 869.6497) 
(list 1920.135 869.66) 
(list 1920 869.66)))
(apply 'command (append '("pline") coords '("c")))
(setq tap6 (ssadd (entlast) tap6))
(command "_mirror" (entlast) "" "1920,900" "1920,901" "No")
(setq tap6 (ssadd (entlast) tap6))
(setq coords (list 
(list 1920.4942 869.29) 
(list 1920.4843 869.29) 
(list 1920.4836 869.3003) 
(list 1920.481 869.3106) 
(list 1920.4766 869.3208) 
(list 1920.4705 869.3311) 
(list 1920.4628 869.3414) 
(list 1920.4538 869.3517) 
(list 1920.4438 869.3619) 
(list 1920.433 869.3722) 
(list 1920.4218 869.3825) 
(list 1920.4105 869.3928) 
(list 1920.3994 869.4031) 
(list 1920.389 869.4133) 
(list 1920.3794 869.4236) 
(list 1920.3711 869.4339) 
(list 1920.3643 869.4442) 
(list 1920.3592 869.4544) 
(list 1920.356 869.4647) 
(list 1920.3547 869.475) 
(list 1920.3556 869.4853) 
(list 1920.3584 869.4956) 
(list 1920.3632 869.5058) 
(list 1920.3698 869.5161) 
(list 1920.3781 869.5264) 
(list 1920.3878 869.5367) 
(list 1920.3986 869.5469) 
(list 1920.4102 869.5572) 
(list 1920.4222 869.5675) 
(list 1920.4344 869.5778) 
(list 1920.4462 869.5881) 
(list 1920.4574 869.5983) 
(list 1920.4676 869.6086) 
(list 1920.4766 869.6189) 
(list 1920.4839 869.6292) 
(list 1920.4894 869.6394) 
(list 1920.4928 869.6497) 
(list 1920.4942 869.66) 
(list 1920.4942 869.66)))
(apply 'command (append '("pline") coords '("c")))
(setq tap6 (ssadd (entlast) tap6))
(command "_mirror" (entlast) "" "1920,900" "1920,901" "No")
(setq tap6 (ssadd (entlast) tap6))
(setq coords (list 
(list 1921.127 869.29) 
(list 1920.4942 869.29) 
(list 1920.4942 869.3003) 
(list 1920.4942 869.3106) 
(list 1920.4942 869.3208) 
(list 1920.4942 869.3311) 
(list 1920.4942 869.3414) 
(list 1920.4942 869.3517) 
(list 1920.4942 869.3619) 
(list 1920.4942 869.3722) 
(list 1920.4942 869.3825) 
(list 1920.4942 869.3928) 
(list 1920.4942 869.4031) 
(list 1920.4942 869.4133) 
(list 1920.4942 869.4236) 
(list 1920.4942 869.4339) 
(list 1920.4942 869.4442) 
(list 1920.4942 869.4544) 
(list 1920.4942 869.4647) 
(list 1920.4942 869.475) 
(list 1920.4942 869.4853) 
(list 1920.4942 869.4956) 
(list 1920.4942 869.5058) 
(list 1920.4942 869.5161) 
(list 1920.4942 869.5264) 
(list 1920.4942 869.5367) 
(list 1920.4942 869.5469) 
(list 1920.4942 869.5572) 
(list 1920.4942 869.5675) 
(list 1920.4942 869.5778) 
(list 1920.4942 869.5881) 
(list 1920.4942 869.5983) 
(list 1920.4942 869.6086) 
(list 1920.4942 869.6189) 
(list 1920.4942 869.6292) 
(list 1920.4942 869.6394) 
(list 1920.4942 869.6497) 
(list 1920.4942 869.66) 
(list 1921.127 869.66)))
(apply 'command (append '("pline") coords '("c")))
(setq tap6 (ssadd (entlast) tap6))
(command "_mirror" (entlast) "" "1920,900" "1920,901" "No")
(setq tap6 (ssadd (entlast) tap6))
(setq coords (list 
(list 1920 869.66) 
(list 1920.135 869.66) 
(list 1920.135 869.6703) 
(list 1920.135 869.6806) 
(list 1920.135 869.6908) 
(list 1920.135 869.7011) 
(list 1920.135 869.7114) 
(list 1920.135 869.7217) 
(list 1920.135 869.7319) 
(list 1920.135 869.7422) 
(list 1920.135 869.7525) 
(list 1920.135 869.7628) 
(list 1920.135 869.7731) 
(list 1920.135 869.7833) 
(list 1920.135 869.7936) 
(list 1920.135 869.8039) 
(list 1920.135 869.8142) 
(list 1920.135 869.8244) 
(list 1920.135 869.8347) 
(list 1920.135 869.845) 
(list 1920.135 869.8553) 
(list 1920.135 869.8656) 
(list 1920.135 869.8758) 
(list 1920.135 869.8861) 
(list 1920.135 869.8964) 
(list 1920.135 869.9067) 
(list 1920.135 869.9169) 
(list 1920.135 869.9272) 
(list 1920.135 869.9375) 
(list 1920.135 869.9478) 
(list 1920.135 869.9581) 
(list 1920.135 869.9683) 
(list 1920.135 869.9786) 
(list 1920.135 869.9889) 
(list 1920.135 869.9992) 
(list 1920.135 870.0094) 
(list 1920.135 870.0197) 
(list 1920.135 870.03) 
(list 1920 870.03)))
(apply 'command (append '("pline") coords '("c")))
(setq tap6 (ssadd (entlast) tap6))
(command "_mirror" (entlast) "" "1920,900" "1920,901" "No")
(setq tap6 (ssadd (entlast) tap6))
(setq coords (list 
(list 1920.5041 869.66) 
(list 1920.4942 869.66) 
(list 1920.4934 869.6703) 
(list 1920.4904 869.6806) 
(list 1920.4853 869.6908) 
(list 1920.4783 869.7011) 
(list 1920.4695 869.7114) 
(list 1920.4592 869.7217) 
(list 1920.4478 869.7319) 
(list 1920.4355 869.7422) 
(list 1920.4227 869.7525) 
(list 1920.4098 869.7628) 
(list 1920.3973 869.7731) 
(list 1920.3854 869.7833) 
(list 1920.3746 869.7936) 
(list 1920.3652 869.8039) 
(list 1920.3575 869.8142) 
(list 1920.3517 869.8244) 
(list 1920.3481 869.8347) 
(list 1920.3467 869.845) 
(list 1920.3477 869.8553) 
(list 1920.3509 869.8656) 
(list 1920.3564 869.8758) 
(list 1920.3639 869.8861) 
(list 1920.3733 869.8964) 
(list 1920.3842 869.9067) 
(list 1920.3965 869.9169) 
(list 1920.4096 869.9272) 
(list 1920.4232 869.9375) 
(list 1920.4369 869.9478) 
(list 1920.4502 869.9581) 
(list 1920.4628 869.9683) 
(list 1920.4743 869.9786) 
(list 1920.4844 869.9889) 
(list 1920.4926 869.9992) 
(list 1920.4987 870.0094) 
(list 1920.5026 870.0197) 
(list 1920.5041 870.03) 
(list 1920.5041 870.03)))
(apply 'command (append '("pline") coords '("c")))
(setq tap6 (ssadd (entlast) tap6))
(command "_mirror" (entlast) "" "1920,900" "1920,901" "No")
(setq tap6 (ssadd (entlast) tap6))
(setq coords (list 
(list 1921.127 869.66) 
(list 1920.5041 869.66) 
(list 1920.5041 869.6703) 
(list 1920.5041 869.6806) 
(list 1920.5041 869.6908) 
(list 1920.5041 869.7011) 
(list 1920.5041 869.7114) 
(list 1920.5041 869.7217) 
(list 1920.5041 869.7319) 
(list 1920.5041 869.7422) 
(list 1920.5041 869.7525) 
(list 1920.5041 869.7628) 
(list 1920.5041 869.7731) 
(list 1920.5041 869.7833) 
(list 1920.5041 869.7936) 
(list 1920.5041 869.8039) 
(list 1920.5041 869.8142) 
(list 1920.5041 869.8244) 
(list 1920.5041 869.8347) 
(list 1920.5041 869.845) 
(list 1920.5041 869.8553) 
(list 1920.5041 869.8656) 
(list 1920.5041 869.8758) 
(list 1920.5041 869.8861) 
(list 1920.5041 869.8964) 
(list 1920.5041 869.9067) 
(list 1920.5041 869.9169) 
(list 1920.5041 869.9272) 
(list 1920.5041 869.9375) 
(list 1920.5041 869.9478) 
(list 1920.5041 869.9581) 
(list 1920.5041 869.9683) 
(list 1920.5041 869.9786) 
(list 1920.5041 869.9889) 
(list 1920.5041 869.9992) 
(list 1920.5041 870.0094) 
(list 1920.5041 870.0197) 
(list 1920.5041 870.03) 
(list 1921.127 870.03)))
(apply 'command (append '("pline") coords '("c")))
(setq tap6 (ssadd (entlast) tap6))
(command "_mirror" (entlast) "" "1920,900" "1920,901" "No")
(setq tap6 (ssadd (entlast) tap6))
(setq coords (list 
(list 1920 870.03) 
(list 1920.135 870.03) 
(list 1920.135 870.0403) 
(list 1920.135 870.0506) 
(list 1920.135 870.0608) 
(list 1920.135 870.0711) 
(list 1920.135 870.0814) 
(list 1920.135 870.0917) 
(list 1920.135 870.1019) 
(list 1920.135 870.1122) 
(list 1920.135 870.1225) 
(list 1920.135 870.1328) 
(list 1920.135 870.1431) 
(list 1920.135 870.1533) 
(list 1920.135 870.1636) 
(list 1920.135 870.1739) 
(list 1920.135 870.1842) 
(list 1920.135 870.1944) 
(list 1920.135 870.2047) 
(list 1920.135 870.215) 
(list 1920.135 870.2253) 
(list 1920.135 870.2356) 
(list 1920.135 870.2458) 
(list 1920.135 870.2561) 
(list 1920.135 870.2664) 
(list 1920.135 870.2767) 
(list 1920.135 870.2869) 
(list 1920.135 870.2972) 
(list 1920.135 870.3075) 
(list 1920.135 870.3178) 
(list 1920.135 870.3281) 
(list 1920.135 870.3383) 
(list 1920.135 870.3486) 
(list 1920.135 870.3589) 
(list 1920.135 870.3692) 
(list 1920.135 870.3794) 
(list 1920.135 870.3897) 
(list 1920.135 870.4) 
(list 1920 870.4)))
(apply 'command (append '("pline") coords '("c")))
(setq tap6 (ssadd (entlast) tap6))
(command "_mirror" (entlast) "" "1920,900" "1920,901" "No")
(setq tap6 (ssadd (entlast) tap6))
(setq coords (list 
(list 1920.514 870.03) 
(list 1920.5041 870.03) 
(list 1920.5031 870.0403) 
(list 1920.4998 870.0506) 
(list 1920.494 870.0608) 
(list 1920.4861 870.0711) 
(list 1920.4762 870.0814) 
(list 1920.4647 870.0917) 
(list 1920.4518 870.1019) 
(list 1920.438 870.1122) 
(list 1920.4236 870.1225) 
(list 1920.4092 870.1328) 
(list 1920.3951 870.1431) 
(list 1920.3819 870.1533) 
(list 1920.3698 870.1636) 
(list 1920.3593 870.1739) 
(list 1920.3507 870.1842) 
(list 1920.3442 870.1944) 
(list 1920.3402 870.2047) 
(list 1920.3387 870.215) 
(list 1920.3398 870.2253) 
(list 1920.3434 870.2356) 
(list 1920.3495 870.2458) 
(list 1920.358 870.2561) 
(list 1920.3684 870.2664) 
(list 1920.3807 870.2767) 
(list 1920.3943 870.2869) 
(list 1920.4089 870.2972) 
(list 1920.4241 870.3075) 
(list 1920.4394 870.3178) 
(list 1920.4542 870.3281) 
(list 1920.4683 870.3383) 
(list 1920.481 870.3486) 
(list 1920.4922 870.3589) 
(list 1920.5013 870.3692) 
(list 1920.5081 870.3794) 
(list 1920.5124 870.3897) 
(list 1920.514 870.4) 
(list 1920.514 870.4)))
(apply 'command (append '("pline") coords '("c")))
(setq tap6 (ssadd (entlast) tap6))
(command "_mirror" (entlast) "" "1920,900" "1920,901" "No")
(setq tap6 (ssadd (entlast) tap6))
(setq coords (list 
(list 1921.127 870.03) 
(list 1920.514 870.03) 
(list 1920.514 870.0403) 
(list 1920.514 870.0506) 
(list 1920.514 870.0608) 
(list 1920.514 870.0711) 
(list 1920.514 870.0814) 
(list 1920.514 870.0917) 
(list 1920.514 870.1019) 
(list 1920.514 870.1122) 
(list 1920.514 870.1225) 
(list 1920.514 870.1328) 
(list 1920.514 870.1431) 
(list 1920.514 870.1533) 
(list 1920.514 870.1636) 
(list 1920.514 870.1739) 
(list 1920.514 870.1842) 
(list 1920.514 870.1944) 
(list 1920.514 870.2047) 
(list 1920.514 870.215) 
(list 1920.514 870.2253) 
(list 1920.514 870.2356) 
(list 1920.514 870.2458) 
(list 1920.514 870.2561) 
(list 1920.514 870.2664) 
(list 1920.514 870.2767) 
(list 1920.514 870.2869) 
(list 1920.514 870.2972) 
(list 1920.514 870.3075) 
(list 1920.514 870.3178) 
(list 1920.514 870.3281) 
(list 1920.514 870.3383) 
(list 1920.514 870.3486) 
(list 1920.514 870.3589) 
(list 1920.514 870.3692) 
(list 1920.514 870.3794) 
(list 1920.514 870.3897) 
(list 1920.514 870.4) 
(list 1921.127 870.4)))
(apply 'command (append '("pline") coords '("c")))
(setq tap6 (ssadd (entlast) tap6))
(command "_mirror" (entlast) "" "1920,900" "1920,901" "No")
(setq tap6 (ssadd (entlast) tap6))
(setq coords (list 
(list 1920 870.4) 
(list 1920.135 870.4) 
(list 1920.135 870.4103) 
(list 1920.135 870.4206) 
(list 1920.135 870.4308) 
(list 1920.135 870.4411) 
(list 1920.135 870.4514) 
(list 1920.135 870.4617) 
(list 1920.135 870.4719) 
(list 1920.135 870.4822) 
(list 1920.135 870.4925) 
(list 1920.135 870.5028) 
(list 1920.135 870.5131) 
(list 1920.135 870.5233) 
(list 1920.135 870.5336) 
(list 1920.135 870.5439) 
(list 1920.135 870.5542) 
(list 1920.135 870.5644) 
(list 1920.135 870.5747) 
(list 1920.135 870.585) 
(list 1920.135 870.5953) 
(list 1920.135 870.6056) 
(list 1920.135 870.6158) 
(list 1920.135 870.6261) 
(list 1920.135 870.6364) 
(list 1920.135 870.6467) 
(list 1920.135 870.6569) 
(list 1920.135 870.6672) 
(list 1920.135 870.6775) 
(list 1920.135 870.6878) 
(list 1920.135 870.6981) 
(list 1920.135 870.7083) 
(list 1920.135 870.7186) 
(list 1920.135 870.7289) 
(list 1920.135 870.7392) 
(list 1920.135 870.7494) 
(list 1920.135 870.7597) 
(list 1920.135 870.77) 
(list 1920 870.77)))
(apply 'command (append '("pline") coords '("c")))
(setq tap6 (ssadd (entlast) tap6))
(command "_mirror" (entlast) "" "1920,900" "1920,901" "No")
(setq tap6 (ssadd (entlast) tap6))
(setq coords (list 
(list 1920.5239 870.4) 
(list 1920.514 870.4) 
(list 1920.5129 870.4103) 
(list 1920.5091 870.4206) 
(list 1920.5027 870.4308) 
(list 1920.4939 870.4411) 
(list 1920.4829 870.4514) 
(list 1920.4701 870.4617) 
(list 1920.4558 870.4719) 
(list 1920.4405 870.4822) 
(list 1920.4246 870.4925) 
(list 1920.4086 870.5028) 
(list 1920.393 870.5131) 
(list 1920.3783 870.5233) 
(list 1920.365 870.5336) 
(list 1920.3533 870.5439) 
(list 1920.3438 870.5542) 
(list 1920.3367 870.5644) 
(list 1920.3323 870.5747) 
(list 1920.3307 870.585) 
(list 1920.3319 870.5953) 
(list 1920.3359 870.6056) 
(list 1920.3427 870.6158) 
(list 1920.352 870.6261) 
(list 1920.3636 870.6364) 
(list 1920.3771 870.6467) 
(list 1920.3922 870.6569) 
(list 1920.4083 870.6672) 
(list 1920.425 870.6775) 
(list 1920.4418 870.6878) 
(list 1920.4582 870.6981) 
(list 1920.4737 870.7083) 
(list 1920.4877 870.7186) 
(list 1920.5 870.7289) 
(list 1920.51 870.7392) 
(list 1920.5174 870.7494) 
(list 1920.5221 870.7597) 
(list 1920.5239 870.77) 
(list 1920.5239 870.77)))
(apply 'command (append '("pline") coords '("c")))
(setq tap6 (ssadd (entlast) tap6))
(command "_mirror" (entlast) "" "1920,900" "1920,901" "No")
(setq tap6 (ssadd (entlast) tap6))
(setq coords (list 
(list 1921.127 870.4) 
(list 1920.5239 870.4) 
(list 1920.5239 870.4103) 
(list 1920.5239 870.4206) 
(list 1920.5239 870.4308) 
(list 1920.5239 870.4411) 
(list 1920.5239 870.4514) 
(list 1920.5239 870.4617) 
(list 1920.5239 870.4719) 
(list 1920.5239 870.4822) 
(list 1920.5239 870.4925) 
(list 1920.5239 870.5028) 
(list 1920.5239 870.5131) 
(list 1920.5239 870.5233) 
(list 1920.5239 870.5336) 
(list 1920.5239 870.5439) 
(list 1920.5239 870.5542) 
(list 1920.5239 870.5644) 
(list 1920.5239 870.5747) 
(list 1920.5239 870.585) 
(list 1920.5239 870.5953) 
(list 1920.5239 870.6056) 
(list 1920.5239 870.6158) 
(list 1920.5239 870.6261) 
(list 1920.5239 870.6364) 
(list 1920.5239 870.6467) 
(list 1920.5239 870.6569) 
(list 1920.5239 870.6672) 
(list 1920.5239 870.6775) 
(list 1920.5239 870.6878) 
(list 1920.5239 870.6981) 
(list 1920.5239 870.7083) 
(list 1920.5239 870.7186) 
(list 1920.5239 870.7289) 
(list 1920.5239 870.7392) 
(list 1920.5239 870.7494) 
(list 1920.5239 870.7597) 
(list 1920.5239 870.77) 
(list 1921.127 870.77)))
(apply 'command (append '("pline") coords '("c")))
(setq tap6 (ssadd (entlast) tap6))
(command "_mirror" (entlast) "" "1920,900" "1920,901" "No")
(setq tap6 (ssadd (entlast) tap6))
(setq coords (list 
(list 1920 870.77) 
(list 1920.135 870.77) 
(list 1920.135 870.7803) 
(list 1920.135 870.7906) 
(list 1920.135 870.8008) 
(list 1920.135 870.8111) 
(list 1920.135 870.8214) 
(list 1920.135 870.8317) 
(list 1920.135 870.8419) 
(list 1920.135 870.8522) 
(list 1920.135 870.8625) 
(list 1920.135 870.8728) 
(list 1920.135 870.8831) 
(list 1920.135 870.8933) 
(list 1920.135 870.9036) 
(list 1920.135 870.9139) 
(list 1920.135 870.9242) 
(list 1920.135 870.9344) 
(list 1920.135 870.9447) 
(list 1920.135 870.955) 
(list 1920.135 870.9653) 
(list 1920.135 870.9756) 
(list 1920.135 870.9858) 
(list 1920.135 870.9961) 
(list 1920.135 871.0064) 
(list 1920.135 871.0167) 
(list 1920.135 871.0269) 
(list 1920.135 871.0372) 
(list 1920.135 871.0475) 
(list 1920.135 871.0578) 
(list 1920.135 871.0681) 
(list 1920.135 871.0783) 
(list 1920.135 871.0886) 
(list 1920.135 871.0989) 
(list 1920.135 871.1092) 
(list 1920.135 871.1194) 
(list 1920.135 871.1297) 
(list 1920.135 871.14) 
(list 1920 871.14)))
(apply 'command (append '("pline") coords '("c")))
(setq tap6 (ssadd (entlast) tap6))
(command "_mirror" (entlast) "" "1920,900" "1920,901" "No")
(setq tap6 (ssadd (entlast) tap6))
(setq coords (list 
(list 1920.5338 870.77) 
(list 1920.5239 870.77) 
(list 1920.5227 870.7803) 
(list 1920.5185 870.7906) 
(list 1920.5114 870.8008) 
(list 1920.5017 870.8111) 
(list 1920.4896 870.8214) 
(list 1920.4755 870.8317) 
(list 1920.4598 870.8419) 
(list 1920.4429 870.8522) 
(list 1920.4255 870.8625) 
(list 1920.408 870.8728) 
(list 1920.3909 870.8831) 
(list 1920.3748 870.8933) 
(list 1920.3601 870.9036) 
(list 1920.3474 870.9139) 
(list 1920.337 870.9242) 
(list 1920.3293 870.9344) 
(list 1920.3244 870.9447) 
(list 1920.3226 870.955) 
(list 1920.324 870.9653) 
(list 1920.3284 870.9756) 
(list 1920.3359 870.9858) 
(list 1920.3461 870.9961) 
(list 1920.3588 871.0064) 
(list 1920.3736 871.0167) 
(list 1920.39 871.0269) 
(list 1920.4077 871.0372) 
(list 1920.426 871.0475) 
(list 1920.4443 871.0578) 
(list 1920.4622 871.0681) 
(list 1920.4791 871.0783) 
(list 1920.4944 871.0886) 
(list 1920.5078 871.0989) 
(list 1920.5187 871.1092) 
(list 1920.5268 871.1194) 
(list 1920.5319 871.1297) 
(list 1920.5338 871.14) 
(list 1920.5338 871.14)))
(apply 'command (append '("pline") coords '("c")))
(setq tap6 (ssadd (entlast) tap6))
(command "_mirror" (entlast) "" "1920,900" "1920,901" "No")
(setq tap6 (ssadd (entlast) tap6))
(setq coords (list 
(list 1921.127 870.77) 
(list 1920.5338 870.77) 
(list 1920.5338 870.7803) 
(list 1920.5338 870.7906) 
(list 1920.5338 870.8008) 
(list 1920.5338 870.8111) 
(list 1920.5338 870.8214) 
(list 1920.5338 870.8317) 
(list 1920.5338 870.8419) 
(list 1920.5338 870.8522) 
(list 1920.5338 870.8625) 
(list 1920.5338 870.8728) 
(list 1920.5338 870.8831) 
(list 1920.5338 870.8933) 
(list 1920.5338 870.9036) 
(list 1920.5338 870.9139) 
(list 1920.5338 870.9242) 
(list 1920.5338 870.9344) 
(list 1920.5338 870.9447) 
(list 1920.5338 870.955) 
(list 1920.5338 870.9653) 
(list 1920.5338 870.9756) 
(list 1920.5338 870.9858) 
(list 1920.5338 870.9961) 
(list 1920.5338 871.0064) 
(list 1920.5338 871.0167) 
(list 1920.5338 871.0269) 
(list 1920.5338 871.0372) 
(list 1920.5338 871.0475) 
(list 1920.5338 871.0578) 
(list 1920.5338 871.0681) 
(list 1920.5338 871.0783) 
(list 1920.5338 871.0886) 
(list 1920.5338 871.0989) 
(list 1920.5338 871.1092) 
(list 1920.5338 871.1194) 
(list 1920.5338 871.1297) 
(list 1920.5338 871.14) 
(list 1921.127 871.14)))
(apply 'command (append '("pline") coords '("c")))
(setq tap6 (ssadd (entlast) tap6))
(command "_mirror" (entlast) "" "1920,900" "1920,901" "No")
(setq tap6 (ssadd (entlast) tap6))
(setq coords (list 
(list 1920 871.14) 
(list 1920.135 871.14) 
(list 1920.135 871.1503) 
(list 1920.135 871.1606) 
(list 1920.135 871.1708) 
(list 1920.135 871.1811) 
(list 1920.135 871.1914) 
(list 1920.135 871.2017) 
(list 1920.135 871.2119) 
(list 1920.135 871.2222) 
(list 1920.135 871.2325) 
(list 1920.135 871.2428) 
(list 1920.135 871.2531) 
(list 1920.135 871.2633) 
(list 1920.135 871.2736) 
(list 1920.135 871.2839) 
(list 1920.135 871.2942) 
(list 1920.135 871.3044) 
(list 1920.135 871.3147) 
(list 1920.135 871.325) 
(list 1920.135 871.3353) 
(list 1920.135 871.3456) 
(list 1920.135 871.3558) 
(list 1920.135 871.3661) 
(list 1920.135 871.3764) 
(list 1920.135 871.3867) 
(list 1920.135 871.3969) 
(list 1920.135 871.4072) 
(list 1920.135 871.4175) 
(list 1920.135 871.4278) 
(list 1920.135 871.4381) 
(list 1920.135 871.4483) 
(list 1920.135 871.4586) 
(list 1920.135 871.4689) 
(list 1920.135 871.4792) 
(list 1920.135 871.4894) 
(list 1920.135 871.4997) 
(list 1920.135 871.51) 
(list 1920 871.51)))
(apply 'command (append '("pline") coords '("c")))
(setq tap6 (ssadd (entlast) tap6))
(command "_mirror" (entlast) "" "1920,900" "1920,901" "No")
(setq tap6 (ssadd (entlast) tap6))
(setq coords (list 
(list 1920.5437 871.14) 
(list 1920.5338 871.14) 
(list 1920.5324 871.1503) 
(list 1920.5278 871.1606) 
(list 1920.5201 871.1708) 
(list 1920.5095 871.1811) 
(list 1920.4963 871.1914) 
(list 1920.4809 871.2017) 
(list 1920.4638 871.2119) 
(list 1920.4454 871.2222) 
(list 1920.4264 871.2325) 
(list 1920.4073 871.2428) 
(list 1920.3887 871.2531) 
(list 1920.3712 871.2633) 
(list 1920.3553 871.2736) 
(list 1920.3415 871.2839) 
(list 1920.3302 871.2942) 
(list 1920.3218 871.3044) 
(list 1920.3165 871.3147) 
(list 1920.3146 871.325) 
(list 1920.3161 871.3353) 
(list 1920.3209 871.3456) 
(list 1920.329 871.3558) 
(list 1920.3401 871.3661) 
(list 1920.3539 871.3764) 
(list 1920.37 871.3867) 
(list 1920.3879 871.3969) 
(list 1920.4071 871.4072) 
(list 1920.4269 871.4175) 
(list 1920.4468 871.4278) 
(list 1920.4662 871.4381) 
(list 1920.4845 871.4483) 
(list 1920.5011 871.4586) 
(list 1920.5156 871.4689) 
(list 1920.5274 871.4792) 
(list 1920.5362 871.4894) 
(list 1920.5417 871.4997) 
(list 1920.5437 871.51) 
(list 1920.5437 871.51)))
(apply 'command (append '("pline") coords '("c")))
(setq tap6 (ssadd (entlast) tap6))
(command "_mirror" (entlast) "" "1920,900" "1920,901" "No")
(setq tap6 (ssadd (entlast) tap6))
(setq coords (list 
(list 1921.127 871.14) 
(list 1920.5437 871.14) 
(list 1920.5437 871.1503) 
(list 1920.5437 871.1606) 
(list 1920.5437 871.1708) 
(list 1920.5437 871.1811) 
(list 1920.5437 871.1914) 
(list 1920.5437 871.2017) 
(list 1920.5437 871.2119) 
(list 1920.5437 871.2222) 
(list 1920.5437 871.2325) 
(list 1920.5437 871.2428) 
(list 1920.5437 871.2531) 
(list 1920.5437 871.2633) 
(list 1920.5437 871.2736) 
(list 1920.5437 871.2839) 
(list 1920.5437 871.2942) 
(list 1920.5437 871.3044) 
(list 1920.5437 871.3147) 
(list 1920.5437 871.325) 
(list 1920.5437 871.3353) 
(list 1920.5437 871.3456) 
(list 1920.5437 871.3558) 
(list 1920.5437 871.3661) 
(list 1920.5437 871.3764) 
(list 1920.5437 871.3867) 
(list 1920.5437 871.3969) 
(list 1920.5437 871.4072) 
(list 1920.5437 871.4175) 
(list 1920.5437 871.4278) 
(list 1920.5437 871.4381) 
(list 1920.5437 871.4483) 
(list 1920.5437 871.4586) 
(list 1920.5437 871.4689) 
(list 1920.5437 871.4792) 
(list 1920.5437 871.4894) 
(list 1920.5437 871.4997) 
(list 1920.5437 871.51) 
(list 1921.127 871.51)))
(apply 'command (append '("pline") coords '("c")))
(setq tap6 (ssadd (entlast) tap6))
(command "_mirror" (entlast) "" "1920,900" "1920,901" "No")
(setq tap6 (ssadd (entlast) tap6))
(setq coords (list 
(list 1920 871.51) 
(list 1920.135 871.51) 
(list 1920.135 871.5203) 
(list 1920.135 871.5306) 
(list 1920.135 871.5408) 
(list 1920.135 871.5511) 
(list 1920.135 871.5614) 
(list 1920.135 871.5717) 
(list 1920.135 871.5819) 
(list 1920.135 871.5922) 
(list 1920.135 871.6025) 
(list 1920.135 871.6128) 
(list 1920.135 871.6231) 
(list 1920.135 871.6333) 
(list 1920.135 871.6436) 
(list 1920.135 871.6539) 
(list 1920.135 871.6642) 
(list 1920.135 871.6744) 
(list 1920.135 871.6847) 
(list 1920.135 871.695) 
(list 1920.135 871.7053) 
(list 1920.135 871.7156) 
(list 1920.135 871.7258) 
(list 1920.135 871.7361) 
(list 1920.135 871.7464) 
(list 1920.135 871.7567) 
(list 1920.135 871.7669) 
(list 1920.135 871.7772) 
(list 1920.135 871.7875) 
(list 1920.135 871.7978) 
(list 1920.135 871.8081) 
(list 1920.135 871.8183) 
(list 1920.135 871.8286) 
(list 1920.135 871.8389) 
(list 1920.135 871.8492) 
(list 1920.135 871.8594) 
(list 1920.135 871.8697) 
(list 1920.135 871.88) 
(list 1920 871.88)))
(apply 'command (append '("pline") coords '("c")))
(setq tap6 (ssadd (entlast) tap6))
(command "_mirror" (entlast) "" "1920,900" "1920,901" "No")
(setq tap6 (ssadd (entlast) tap6))
(setq coords (list 
(list 1920.5536 871.51) 
(list 1920.5437 871.51) 
(list 1920.5422 871.5203) 
(list 1920.5372 871.5306) 
(list 1920.5288 871.5408) 
(list 1920.5173 871.5511) 
(list 1920.503 871.5614) 
(list 1920.4863 871.5717) 
(list 1920.4678 871.5819) 
(list 1920.4479 871.5922) 
(list 1920.4274 871.6025) 
(list 1920.4067 871.6128) 
(list 1920.3866 871.6231) 
(list 1920.3677 871.6333) 
(list 1920.3505 871.6436) 
(list 1920.3355 871.6539) 
(list 1920.3233 871.6642) 
(list 1920.3143 871.6744) 
(list 1920.3086 871.6847) 
(list 1920.3066 871.695) 
(list 1920.3082 871.7053) 
(list 1920.3134 871.7156) 
(list 1920.3222 871.7258) 
(list 1920.3342 871.7361) 
(list 1920.3491 871.7464) 
(list 1920.3665 871.7567) 
(list 1920.3858 871.7669) 
(list 1920.4064 871.7772) 
(list 1920.4278 871.7875) 
(list 1920.4493 871.7978) 
(list 1920.4702 871.8081) 
(list 1920.4899 871.8183) 
(list 1920.5078 871.8286) 
(list 1920.5234 871.8389) 
(list 1920.5361 871.8492) 
(list 1920.5455 871.8594) 
(list 1920.5514 871.8697) 
(list 1920.5536 871.88) 
(list 1920.5536 871.88)))
(apply 'command (append '("pline") coords '("c")))
(setq tap6 (ssadd (entlast) tap6))
(command "_mirror" (entlast) "" "1920,900" "1920,901" "No")
(setq tap6 (ssadd (entlast) tap6))
(setq coords (list 
(list 1921.127 871.51) 
(list 1920.5536 871.51) 
(list 1920.5536 871.5203) 
(list 1920.5536 871.5306) 
(list 1920.5536 871.5408) 
(list 1920.5536 871.5511) 
(list 1920.5536 871.5614) 
(list 1920.5536 871.5717) 
(list 1920.5536 871.5819) 
(list 1920.5536 871.5922) 
(list 1920.5536 871.6025) 
(list 1920.5536 871.6128) 
(list 1920.5536 871.6231) 
(list 1920.5536 871.6333) 
(list 1920.5536 871.6436) 
(list 1920.5536 871.6539) 
(list 1920.5536 871.6642) 
(list 1920.5536 871.6744) 
(list 1920.5536 871.6847) 
(list 1920.5536 871.695) 
(list 1920.5536 871.7053) 
(list 1920.5536 871.7156) 
(list 1920.5536 871.7258) 
(list 1920.5536 871.7361) 
(list 1920.5536 871.7464) 
(list 1920.5536 871.7567) 
(list 1920.5536 871.7669) 
(list 1920.5536 871.7772) 
(list 1920.5536 871.7875) 
(list 1920.5536 871.7978) 
(list 1920.5536 871.8081) 
(list 1920.5536 871.8183) 
(list 1920.5536 871.8286) 
(list 1920.5536 871.8389) 
(list 1920.5536 871.8492) 
(list 1920.5536 871.8594) 
(list 1920.5536 871.8697) 
(list 1920.5536 871.88) 
(list 1921.127 871.88)))
(apply 'command (append '("pline") coords '("c")))
(setq tap6 (ssadd (entlast) tap6))
(command "_mirror" (entlast) "" "1920,900" "1920,901" "No")
(setq tap6 (ssadd (entlast) tap6))
(setq coords (list 
(list 1920 871.88) 
(list 1920.135 871.88) 
(list 1920.135 871.8903) 
(list 1920.135 871.9006) 
(list 1920.135 871.9108) 
(list 1920.135 871.9211) 
(list 1920.135 871.9314) 
(list 1920.135 871.9417) 
(list 1920.135 871.9519) 
(list 1920.135 871.9622) 
(list 1920.135 871.9725) 
(list 1920.135 871.9828) 
(list 1920.135 871.9931) 
(list 1920.135 872.0033) 
(list 1920.135 872.0136) 
(list 1920.135 872.0239) 
(list 1920.135 872.0342) 
(list 1920.135 872.0444) 
(list 1920.135 872.0547) 
(list 1920.135 872.065) 
(list 1920.135 872.0753) 
(list 1920.135 872.0856) 
(list 1920.135 872.0958) 
(list 1920.135 872.1061) 
(list 1920.135 872.1164) 
(list 1920.135 872.1267) 
(list 1920.135 872.1369) 
(list 1920.135 872.1472) 
(list 1920.135 872.1575) 
(list 1920.135 872.1678) 
(list 1920.135 872.1781) 
(list 1920.135 872.1883) 
(list 1920.135 872.1986) 
(list 1920.135 872.2089) 
(list 1920.135 872.2192) 
(list 1920.135 872.2294) 
(list 1920.135 872.2397) 
(list 1920.135 872.25) 
(list 1920 872.25)))
(apply 'command (append '("pline") coords '("c")))
(setq tap6 (ssadd (entlast) tap6))
(command "_mirror" (entlast) "" "1920,900" "1920,901" "No")
(setq tap6 (ssadd (entlast) tap6))
(setq coords (list 
(list 1920.5635 871.88) 
(list 1920.5536 871.88) 
(list 1920.552 871.8903) 
(list 1920.5466 871.9006) 
(list 1920.5375 871.9108) 
(list 1920.5251 871.9211) 
(list 1920.5097 871.9314) 
(list 1920.4917 871.9417) 
(list 1920.4718 871.9519) 
(list 1920.4504 871.9622) 
(list 1920.4283 871.9725) 
(list 1920.4061 871.9828) 
(list 1920.3845 871.9931) 
(list 1920.3641 872.0033) 
(list 1920.3456 872.0136) 
(list 1920.3296 872.0239) 
(list 1920.3165 872.0342) 
(list 1920.3068 872.0444) 
(list 1920.3007 872.0547) 
(list 1920.2985 872.065) 
(list 1920.3003 872.0753) 
(list 1920.3059 872.0856) 
(list 1920.3154 872.0958) 
(list 1920.3283 872.1061) 
(list 1920.3443 872.1164) 
(list 1920.3629 872.1267) 
(list 1920.3836 872.1369) 
(list 1920.4058 872.1472) 
(list 1920.4288 872.1575) 
(list 1920.4518 872.1678) 
(list 1920.4742 872.1781) 
(list 1920.4953 872.1883) 
(list 1920.5145 872.1986) 
(list 1920.5312 872.2089) 
(list 1920.5448 872.2192) 
(list 1920.5549 872.2294) 
(list 1920.5612 872.2397) 
(list 1920.5635 872.25) 
(list 1920.5635 872.25)))
(apply 'command (append '("pline") coords '("c")))
(setq tap6 (ssadd (entlast) tap6))
(command "_mirror" (entlast) "" "1920,900" "1920,901" "No")
(setq tap6 (ssadd (entlast) tap6))
(setq coords (list 
(list 1921.127 871.88) 
(list 1920.5635 871.88) 
(list 1920.5635 871.8903) 
(list 1920.5635 871.9006) 
(list 1920.5635 871.9108) 
(list 1920.5635 871.9211) 
(list 1920.5635 871.9314) 
(list 1920.5635 871.9417) 
(list 1920.5635 871.9519) 
(list 1920.5635 871.9622) 
(list 1920.5635 871.9725) 
(list 1920.5635 871.9828) 
(list 1920.5635 871.9931) 
(list 1920.5635 872.0033) 
(list 1920.5635 872.0136) 
(list 1920.5635 872.0239) 
(list 1920.5635 872.0342) 
(list 1920.5635 872.0444) 
(list 1920.5635 872.0547) 
(list 1920.5635 872.065) 
(list 1920.5635 872.0753) 
(list 1920.5635 872.0856) 
(list 1920.5635 872.0958) 
(list 1920.5635 872.1061) 
(list 1920.5635 872.1164) 
(list 1920.5635 872.1267) 
(list 1920.5635 872.1369) 
(list 1920.5635 872.1472) 
(list 1920.5635 872.1575) 
(list 1920.5635 872.1678) 
(list 1920.5635 872.1781) 
(list 1920.5635 872.1883) 
(list 1920.5635 872.1986) 
(list 1920.5635 872.2089) 
(list 1920.5635 872.2192) 
(list 1920.5635 872.2294) 
(list 1920.5635 872.2397) 
(list 1920.5635 872.25) 
(list 1921.127 872.25)))
(apply 'command (append '("pline") coords '("c")))
(setq tap6 (ssadd (entlast) tap6))
(command "_mirror" (entlast) "" "1920,900" "1920,901" "No")
(setq tap6 (ssadd (entlast) tap6))
(command "_block" "blktap6" "1920,900" tap6 "")
(command "_insert" "blktap6" "1920,900" "1" "1" "0")
(command "_insert" "blktap6" "1920,900" "1" "1" "180")
(setq uc6 nil)
(setq uc6 (ssadd))
(setq coords (list 
(list 0 -0.185) 
(list 0.135 -0.185) 
(list 0.135 -0.17472) 
(list 0.135 -0.16444) 
(list 0.135 -0.15417) 
(list 0.135 -0.14389) 
(list 0.135 -0.13361) 
(list 0.135 -0.12333) 
(list 0.135 -0.11306) 
(list 0.135 -0.10278) 
(list 0.135 -0.0925) 
(list 0.135 -0.082222) 
(list 0.135 -0.071944) 
(list 0.135 -0.061667) 
(list 0.135 -0.051389) 
(list 0.135 -0.041111) 
(list 0.135 -0.030833) 
(list 0.135 -0.020556) 
(list 0.135 -0.010278) 
(list 0.135 0) 
(list 0.135 0.010278) 
(list 0.135 0.020556) 
(list 0.135 0.030833) 
(list 0.135 0.041111) 
(list 0.135 0.051389) 
(list 0.135 0.061667) 
(list 0.135 0.071944) 
(list 0.135 0.082222) 
(list 0.135 0.0925) 
(list 0.135 0.10278) 
(list 0.135 0.11306) 
(list 0.135 0.12333) 
(list 0.135 0.13361) 
(list 0.135 0.14389) 
(list 0.135 0.15417) 
(list 0.135 0.16444) 
(list 0.135 0.17472) 
(list 0.135 0.185) 
(list 0 0.185)))
(apply 'command (append '("pline") coords '("c")))
(setq uc6 (ssadd (entlast) uc6))
(setq coords (list 
(list 1.127 -0.185) 
(list 0.5635 -0.185) 
(list 0.56146 -0.17472) 
(list 0.55539 -0.16444) 
(list 0.54548 -0.15417) 
(list 0.53203 -0.14389) 
(list 0.51545 -0.13361) 
(list 0.49625 -0.12333) 
(list 0.475 -0.11306) 
(list 0.45236 -0.10278) 
(list 0.429 -0.0925) 
(list 0.40564 -0.082222) 
(list 0.383 -0.071944) 
(list 0.36175 -0.061667) 
(list 0.34254 -0.051389) 
(list 0.32597 -0.041111) 
(list 0.31252 -0.030833) 
(list 0.30261 -0.020556) 
(list 0.29654 -0.010278) 
(list 0.2945 0) 
(list 0.29654 0.010278) 
(list 0.30261 0.020556) 
(list 0.31252 0.030833) 
(list 0.32597 0.041111) 
(list 0.34254 0.051389) 
(list 0.36175 0.061667) 
(list 0.383 0.071944) 
(list 0.40564 0.082222) 
(list 0.429 0.0925) 
(list 0.45236 0.10278) 
(list 0.475 0.11306) 
(list 0.49625 0.12333) 
(list 0.51545 0.13361) 
(list 0.53203 0.14389) 
(list 0.54548 0.15417) 
(list 0.55539 0.16444) 
(list 0.56146 0.17472) 
(list 0.5635 0.185) 
(list 1.127 0.185)))
(apply 'command (append '("pline") coords '("c")))
(setq uc6 (ssadd (entlast) uc6))
(command "_block" "blkuc6" "0,0.185" uc6 "")
(command "_insert" "blkuc6" "1920,872.62" "1" "1" "0")
(command "_insert" "blkuc6" "1920,872.25" "1" "1" "180")
(command "_insert" "blkuc6" "1920,872.99" "1" "1" "0")
(command "_insert" "blkuc6" "1920,872.62" "1" "1" "180")
(command "_insert" "blkuc6" "1920,873.36" "1" "1" "0")
(command "_insert" "blkuc6" "1920,872.99" "1" "1" "180")
(command "_insert" "blkuc6" "1920,873.73" "1" "1" "0")
(command "_insert" "blkuc6" "1920,873.36" "1" "1" "180")
(command "_insert" "blkuc6" "1920,874.1" "1" "1" "0")
(command "_insert" "blkuc6" "1920,873.73" "1" "1" "180")
(command "_insert" "blkuc6" "1920,874.47" "1" "1" "0")
(command "_insert" "blkuc6" "1920,874.1" "1" "1" "180")
(command "_insert" "blkuc6" "1920,874.84" "1" "1" "0")
(command "_insert" "blkuc6" "1920,874.47" "1" "1" "180")
(command "_insert" "blkuc6" "1920,875.21" "1" "1" "0")
(command "_insert" "blkuc6" "1920,874.84" "1" "1" "180")
(command "_insert" "blkuc6" "1920,875.58" "1" "1" "0")
(command "_insert" "blkuc6" "1920,875.21" "1" "1" "180")
(command "_insert" "blkuc6" "1920,875.95" "1" "1" "0")
(command "_insert" "blkuc6" "1920,875.58" "1" "1" "180")
(command "_insert" "blkuc6" "1920,876.32" "1" "1" "0")
(command "_insert" "blkuc6" "1920,875.95" "1" "1" "180")
(command "_insert" "blkuc6" "1920,876.69" "1" "1" "0")
(command "_insert" "blkuc6" "1920,876.32" "1" "1" "180")
(command "_insert" "blkuc6" "1920,877.06" "1" "1" "0")
(command "_insert" "blkuc6" "1920,876.69" "1" "1" "180")
(command "_insert" "blkuc6" "1920,877.43" "1" "1" "0")
(command "_insert" "blkuc6" "1920,877.06" "1" "1" "180")
(command "_insert" "blkuc6" "1920,877.8" "1" "1" "0")
(command "_insert" "blkuc6" "1920,877.43" "1" "1" "180")
(command "_insert" "blkuc6" "1920,878.17" "1" "1" "0")
(command "_insert" "blkuc6" "1920,877.8" "1" "1" "180")
(command "_insert" "blkuc6" "1920,878.54" "1" "1" "0")
(command "_insert" "blkuc6" "1920,878.17" "1" "1" "180")
(command "_insert" "blkuc6" "1920,878.91" "1" "1" "0")
(command "_insert" "blkuc6" "1920,878.54" "1" "1" "180")
(command "_insert" "blkuc6" "1920,879.28" "1" "1" "0")
(command "_insert" "blkuc6" "1920,878.91" "1" "1" "180")
(command "_insert" "blkuc6" "1920,879.65" "1" "1" "0")
(command "_insert" "blkuc6" "1920,879.28" "1" "1" "180")
(command "_insert" "blkuc6" "1920,880.02" "1" "1" "0")
(command "_insert" "blkuc6" "1920,879.65" "1" "1" "180")
(command "_insert" "blkuc6" "1920,880.39" "1" "1" "0")
(command "_insert" "blkuc6" "1920,880.02" "1" "1" "180")
(command "_insert" "blkuc6" "1920,880.76" "1" "1" "0")
(command "_insert" "blkuc6" "1920,880.39" "1" "1" "180")
(command "_insert" "blkuc6" "1920,881.13" "1" "1" "0")
(command "_insert" "blkuc6" "1920,880.76" "1" "1" "180")
(command "_insert" "blkuc6" "1920,881.5" "1" "1" "0")
(command "_insert" "blkuc6" "1920,881.13" "1" "1" "180")
(command "_insert" "blkuc6" "1920,881.87" "1" "1" "0")
(command "_insert" "blkuc6" "1920,881.5" "1" "1" "180")
(command "_insert" "blkuc6" "1920,882.24" "1" "1" "0")
(command "_insert" "blkuc6" "1920,881.87" "1" "1" "180")
(command "_insert" "blkuc6" "1920,882.61" "1" "1" "0")
(command "_insert" "blkuc6" "1920,882.24" "1" "1" "180")
(command "_insert" "blkuc6" "1920,882.98" "1" "1" "0")
(command "_insert" "blkuc6" "1920,882.61" "1" "1" "180")
(command "_insert" "blkuc6" "1920,883.35" "1" "1" "0")
(command "_insert" "blkuc6" "1920,882.98" "1" "1" "180")
(command "_insert" "blkuc6" "1920,883.72" "1" "1" "0")
(command "_insert" "blkuc6" "1920,883.35" "1" "1" "180")
(command "_insert" "blkuc6" "1920,884.09" "1" "1" "0")
(command "_insert" "blkuc6" "1920,883.72" "1" "1" "180")
(command "_insert" "blkuc6" "1920,884.46" "1" "1" "0")
(command "_insert" "blkuc6" "1920,884.09" "1" "1" "180")
(command "_insert" "blkuc6" "1920,884.83" "1" "1" "0")
(command "_insert" "blkuc6" "1920,884.46" "1" "1" "180")
(command "_insert" "blkuc6" "1920,885.2" "1" "1" "0")
(command "_insert" "blkuc6" "1920,884.83" "1" "1" "180")
(command "_insert" "blkuc6" "1920,885.57" "1" "1" "0")
(command "_insert" "blkuc6" "1920,885.2" "1" "1" "180")
(command "_insert" "blkuc6" "1920,885.94" "1" "1" "0")
(command "_insert" "blkuc6" "1920,885.57" "1" "1" "180")
(command "_insert" "blkuc6" "1920,886.31" "1" "1" "0")
(command "_insert" "blkuc6" "1920,885.94" "1" "1" "180")
(command "_insert" "blkuc6" "1920,886.68" "1" "1" "0")
(command "_insert" "blkuc6" "1920,886.31" "1" "1" "180")
(command "_insert" "blkuc6" "1920,887.05" "1" "1" "0")
(command "_insert" "blkuc6" "1920,886.68" "1" "1" "180")
(command "_insert" "blkuc6" "1920,887.42" "1" "1" "0")
(command "_insert" "blkuc6" "1920,887.05" "1" "1" "180")
(command "_insert" "blkuc6" "1920,887.79" "1" "1" "0")
(command "_insert" "blkuc6" "1920,887.42" "1" "1" "180")
(command "_insert" "blkuc6" "1920,888.16" "1" "1" "0")
(command "_insert" "blkuc6" "1920,887.79" "1" "1" "180")
(command "_insert" "blkuc6" "1920,888.53" "1" "1" "0")
(command "_insert" "blkuc6" "1920,888.16" "1" "1" "180")
(command "_insert" "blkuc6" "1920,888.9" "1" "1" "0")
(command "_insert" "blkuc6" "1920,888.53" "1" "1" "180")
(command "_insert" "blkuc6" "1920,889.27" "1" "1" "0")
(command "_insert" "blkuc6" "1920,888.9" "1" "1" "180")
(command "_insert" "blkuc6" "1920,889.64" "1" "1" "0")
(command "_insert" "blkuc6" "1920,889.27" "1" "1" "180")
(command "_insert" "blkuc6" "1920,890.01" "1" "1" "0")
(command "_insert" "blkuc6" "1920,889.64" "1" "1" "180")
(command "_insert" "blkuc6" "1920,890.38" "1" "1" "0")
(command "_insert" "blkuc6" "1920,890.01" "1" "1" "180")
(command "_insert" "blkuc6" "1920,890.75" "1" "1" "0")
(command "_insert" "blkuc6" "1920,890.38" "1" "1" "180")
(command "_insert" "blkuc6" "1920,891.12" "1" "1" "0")
(command "_insert" "blkuc6" "1920,890.75" "1" "1" "180")
(command "_insert" "blkuc6" "1920,891.49" "1" "1" "0")
(command "_insert" "blkuc6" "1920,891.12" "1" "1" "180")
(command "_insert" "blkuc6" "1920,891.86" "1" "1" "0")
(command "_insert" "blkuc6" "1920,891.49" "1" "1" "180")
(command "_insert" "blkuc6" "1920,892.23" "1" "1" "0")
(command "_insert" "blkuc6" "1920,891.86" "1" "1" "180")
(command "_insert" "blkuc6" "1920,892.6" "1" "1" "0")
(command "_insert" "blkuc6" "1920,892.23" "1" "1" "180")
(command "_insert" "blkuc6" "1920,892.97" "1" "1" "0")
(command "_insert" "blkuc6" "1920,892.6" "1" "1" "180")
(command "_insert" "blkuc6" "1920,893.34" "1" "1" "0")
(command "_insert" "blkuc6" "1920,892.97" "1" "1" "180")
(command "_insert" "blkuc6" "1920,893.71" "1" "1" "0")
(command "_insert" "blkuc6" "1920,893.34" "1" "1" "180")
(command "_insert" "blkuc6" "1920,894.08" "1" "1" "0")
(command "_insert" "blkuc6" "1920,893.71" "1" "1" "180")
(command "_insert" "blkuc6" "1920,894.45" "1" "1" "0")
(command "_insert" "blkuc6" "1920,894.08" "1" "1" "180")
(command "_insert" "blkuc6" "1920,894.82" "1" "1" "0")
(command "_insert" "blkuc6" "1920,894.45" "1" "1" "180")
(command "_insert" "blkuc6" "1920,895.19" "1" "1" "0")
(command "_insert" "blkuc6" "1920,894.82" "1" "1" "180")
(command "_insert" "blkuc6" "1920,895.56" "1" "1" "0")
(command "_insert" "blkuc6" "1920,895.19" "1" "1" "180")
(command "_insert" "blkuc6" "1920,895.93" "1" "1" "0")
(command "_insert" "blkuc6" "1920,895.56" "1" "1" "180")
(command "_insert" "blkuc6" "1920,896.3" "1" "1" "0")
(command "_insert" "blkuc6" "1920,895.93" "1" "1" "180")
(command "_insert" "blkuc6" "1920,896.67" "1" "1" "0")
(command "_insert" "blkuc6" "1920,896.3" "1" "1" "180")
(command "_insert" "blkuc6" "1920,897.04" "1" "1" "0")
(command "_insert" "blkuc6" "1920,896.67" "1" "1" "180")
(command "_insert" "blkuc6" "1920,897.41" "1" "1" "0")
(command "_insert" "blkuc6" "1920,897.04" "1" "1" "180")
(command "_insert" "blkuc6" "1920,897.78" "1" "1" "0")
(command "_insert" "blkuc6" "1920,897.41" "1" "1" "180")
(command "_insert" "blkuc6" "1920,898.15" "1" "1" "0")
(command "_insert" "blkuc6" "1920,897.78" "1" "1" "180")
(command "_insert" "blkuc6" "1920,898.52" "1" "1" "0")
(command "_insert" "blkuc6" "1920,898.15" "1" "1" "180")
(command "_insert" "blkuc6" "1920,898.89" "1" "1" "0")
(command "_insert" "blkuc6" "1920,898.52" "1" "1" "180")
(command "_insert" "blkuc6" "1920,899.26" "1" "1" "0")
(command "_insert" "blkuc6" "1920,898.89" "1" "1" "180")
(command "_insert" "blkuc6" "1920,899.63" "1" "1" "0")
(command "_insert" "blkuc6" "1920,899.26" "1" "1" "180")
(command "_insert" "blkuc6" "1920,900" "1" "1" "0")
(command "_insert" "blkuc6" "1920,899.63" "1" "1" "180")
(command "_insert" "blkuc6" "1920,900.37" "1" "1" "0")
(command "_insert" "blkuc6" "1920,900" "1" "1" "180")
(command "_insert" "blkuc6" "1920,900.74" "1" "1" "0")
(command "_insert" "blkuc6" "1920,900.37" "1" "1" "180")
(command "_insert" "blkuc6" "1920,901.11" "1" "1" "0")
(command "_insert" "blkuc6" "1920,900.74" "1" "1" "180")
(command "_insert" "blkuc6" "1920,901.48" "1" "1" "0")
(command "_insert" "blkuc6" "1920,901.11" "1" "1" "180")
(command "_insert" "blkuc6" "1920,901.85" "1" "1" "0")
(command "_insert" "blkuc6" "1920,901.48" "1" "1" "180")
(command "_insert" "blkuc6" "1920,902.22" "1" "1" "0")
(command "_insert" "blkuc6" "1920,901.85" "1" "1" "180")
(command "_insert" "blkuc6" "1920,902.59" "1" "1" "0")
(command "_insert" "blkuc6" "1920,902.22" "1" "1" "180")
(command "_insert" "blkuc6" "1920,902.96" "1" "1" "0")
(command "_insert" "blkuc6" "1920,902.59" "1" "1" "180")
(command "_insert" "blkuc6" "1920,903.33" "1" "1" "0")
(command "_insert" "blkuc6" "1920,902.96" "1" "1" "180")
(command "_insert" "blkuc6" "1920,903.7" "1" "1" "0")
(command "_insert" "blkuc6" "1920,903.33" "1" "1" "180")
(command "_insert" "blkuc6" "1920,904.07" "1" "1" "0")
(command "_insert" "blkuc6" "1920,903.7" "1" "1" "180")
(command "_insert" "blkuc6" "1920,904.44" "1" "1" "0")
(command "_insert" "blkuc6" "1920,904.07" "1" "1" "180")
(command "_insert" "blkuc6" "1920,904.81" "1" "1" "0")
(command "_insert" "blkuc6" "1920,904.44" "1" "1" "180")
(command "_insert" "blkuc6" "1920,905.18" "1" "1" "0")
(command "_insert" "blkuc6" "1920,904.81" "1" "1" "180")
(command "_insert" "blkuc6" "1920,905.55" "1" "1" "0")
(command "_insert" "blkuc6" "1920,905.18" "1" "1" "180")
(command "_insert" "blkuc6" "1920,905.92" "1" "1" "0")
(command "_insert" "blkuc6" "1920,905.55" "1" "1" "180")
(command "_insert" "blkuc6" "1920,906.29" "1" "1" "0")
(command "_insert" "blkuc6" "1920,905.92" "1" "1" "180")
(command "_insert" "blkuc6" "1920,906.66" "1" "1" "0")
(command "_insert" "blkuc6" "1920,906.29" "1" "1" "180")
(command "_insert" "blkuc6" "1920,907.03" "1" "1" "0")
(command "_insert" "blkuc6" "1920,906.66" "1" "1" "180")
(command "_insert" "blkuc6" "1920,907.4" "1" "1" "0")
(command "_insert" "blkuc6" "1920,907.03" "1" "1" "180")
(command "_insert" "blkuc6" "1920,907.77" "1" "1" "0")
(command "_insert" "blkuc6" "1920,907.4" "1" "1" "180")
(command "_insert" "blkuc6" "1920,908.14" "1" "1" "0")
(command "_insert" "blkuc6" "1920,907.77" "1" "1" "180")
(command "_insert" "blkuc6" "1920,908.51" "1" "1" "0")
(command "_insert" "blkuc6" "1920,908.14" "1" "1" "180")
(command "_insert" "blkuc6" "1920,908.88" "1" "1" "0")
(command "_insert" "blkuc6" "1920,908.51" "1" "1" "180")
(command "_insert" "blkuc6" "1920,909.25" "1" "1" "0")
(command "_insert" "blkuc6" "1920,908.88" "1" "1" "180")
(command "_insert" "blkuc6" "1920,909.62" "1" "1" "0")
(command "_insert" "blkuc6" "1920,909.25" "1" "1" "180")
(command "_insert" "blkuc6" "1920,909.99" "1" "1" "0")
(command "_insert" "blkuc6" "1920,909.62" "1" "1" "180")
(command "_insert" "blkuc6" "1920,910.36" "1" "1" "0")
(command "_insert" "blkuc6" "1920,909.99" "1" "1" "180")
(command "_insert" "blkuc6" "1920,910.73" "1" "1" "0")
(command "_insert" "blkuc6" "1920,910.36" "1" "1" "180")
(command "_insert" "blkuc6" "1920,911.1" "1" "1" "0")
(command "_insert" "blkuc6" "1920,910.73" "1" "1" "180")
(command "_insert" "blkuc6" "1920,911.47" "1" "1" "0")
(command "_insert" "blkuc6" "1920,911.1" "1" "1" "180")
(command "_insert" "blkuc6" "1920,911.84" "1" "1" "0")
(command "_insert" "blkuc6" "1920,911.47" "1" "1" "180")
(command "_insert" "blkuc6" "1920,912.21" "1" "1" "0")
(command "_insert" "blkuc6" "1920,911.84" "1" "1" "180")
(command "_insert" "blkuc6" "1920,912.58" "1" "1" "0")
(command "_insert" "blkuc6" "1920,912.21" "1" "1" "180")
(command "_insert" "blkuc6" "1920,912.95" "1" "1" "0")
(command "_insert" "blkuc6" "1920,912.58" "1" "1" "180")
(command "_insert" "blkuc6" "1920,913.32" "1" "1" "0")
(command "_insert" "blkuc6" "1920,912.95" "1" "1" "180")
(command "_insert" "blkuc6" "1920,913.69" "1" "1" "0")
(command "_insert" "blkuc6" "1920,913.32" "1" "1" "180")
(command "_insert" "blkuc6" "1920,914.06" "1" "1" "0")
(command "_insert" "blkuc6" "1920,913.69" "1" "1" "180")
(command "_insert" "blkuc6" "1920,914.43" "1" "1" "0")
(command "_insert" "blkuc6" "1920,914.06" "1" "1" "180")
(command "_insert" "blkuc6" "1920,914.8" "1" "1" "0")
(command "_insert" "blkuc6" "1920,914.43" "1" "1" "180")
(command "_insert" "blkuc6" "1920,915.17" "1" "1" "0")
(command "_insert" "blkuc6" "1920,914.8" "1" "1" "180")
(command "_insert" "blkuc6" "1920,915.54" "1" "1" "0")
(command "_insert" "blkuc6" "1920,915.17" "1" "1" "180")
(command "_insert" "blkuc6" "1920,915.91" "1" "1" "0")
(command "_insert" "blkuc6" "1920,915.54" "1" "1" "180")
(command "_insert" "blkuc6" "1920,916.28" "1" "1" "0")
(command "_insert" "blkuc6" "1920,915.91" "1" "1" "180")
(command "_insert" "blkuc6" "1920,916.65" "1" "1" "0")
(command "_insert" "blkuc6" "1920,916.28" "1" "1" "180")
(command "_insert" "blkuc6" "1920,917.02" "1" "1" "0")
(command "_insert" "blkuc6" "1920,916.65" "1" "1" "180")
(command "_insert" "blkuc6" "1920,917.39" "1" "1" "0")
(command "_insert" "blkuc6" "1920,917.02" "1" "1" "180")
(command "_insert" "blkuc6" "1920,917.76" "1" "1" "0")
(command "_insert" "blkuc6" "1920,917.39" "1" "1" "180")
(command "_insert" "blkuc6" "1920,918.13" "1" "1" "0")
(command "_insert" "blkuc6" "1920,917.76" "1" "1" "180")
(command "_insert" "blkuc6" "1920,918.5" "1" "1" "0")
(command "_insert" "blkuc6" "1920,918.13" "1" "1" "180")
(command "_insert" "blkuc6" "1920,918.87" "1" "1" "0")
(command "_insert" "blkuc6" "1920,918.5" "1" "1" "180")
(command "_insert" "blkuc6" "1920,919.24" "1" "1" "0")
(command "_insert" "blkuc6" "1920,918.87" "1" "1" "180")
(command "_insert" "blkuc6" "1920,919.61" "1" "1" "0")
(command "_insert" "blkuc6" "1920,919.24" "1" "1" "180")
(command "_insert" "blkuc6" "1920,919.98" "1" "1" "0")
(command "_insert" "blkuc6" "1920,919.61" "1" "1" "180")
(command "_insert" "blkuc6" "1920,920.35" "1" "1" "0")
(command "_insert" "blkuc6" "1920,919.98" "1" "1" "180")
(command "_insert" "blkuc6" "1920,920.72" "1" "1" "0")
(command "_insert" "blkuc6" "1920,920.35" "1" "1" "180")
(command "_insert" "blkuc6" "1920,921.09" "1" "1" "0")
(command "_insert" "blkuc6" "1920,920.72" "1" "1" "180")
(command "_insert" "blkuc6" "1920,921.46" "1" "1" "0")
(command "_insert" "blkuc6" "1920,921.09" "1" "1" "180")
(command "_insert" "blkuc6" "1920,921.83" "1" "1" "0")
(command "_insert" "blkuc6" "1920,921.46" "1" "1" "180")
(command "_insert" "blkuc6" "1920,922.2" "1" "1" "0")
(command "_insert" "blkuc6" "1920,921.83" "1" "1" "180")
(command "_insert" "blkuc6" "1920,922.57" "1" "1" "0")
(command "_insert" "blkuc6" "1920,922.2" "1" "1" "180")
(command "_insert" "blkuc6" "1920,922.94" "1" "1" "0")
(command "_insert" "blkuc6" "1920,922.57" "1" "1" "180")
(command "_insert" "blkuc6" "1920,923.31" "1" "1" "0")
(command "_insert" "blkuc6" "1920,922.94" "1" "1" "180")
(command "_insert" "blkuc6" "1920,923.68" "1" "1" "0")
(command "_insert" "blkuc6" "1920,923.31" "1" "1" "180")
(command "_insert" "blkuc6" "1920,924.05" "1" "1" "0")
(command "_insert" "blkuc6" "1920,923.68" "1" "1" "180")
(command "_insert" "blkuc6" "1920,924.42" "1" "1" "0")
(command "_insert" "blkuc6" "1920,924.05" "1" "1" "180")
(command "_insert" "blkuc6" "1920,924.79" "1" "1" "0")
(command "_insert" "blkuc6" "1920,924.42" "1" "1" "180")
(command "_insert" "blkuc6" "1920,925.16" "1" "1" "0")
(command "_insert" "blkuc6" "1920,924.79" "1" "1" "180")
(command "_insert" "blkuc6" "1920,925.53" "1" "1" "0")
(command "_insert" "blkuc6" "1920,925.16" "1" "1" "180")
(command "_insert" "blkuc6" "1920,925.9" "1" "1" "0")
(command "_insert" "blkuc6" "1920,925.53" "1" "1" "180")
(command "_insert" "blkuc6" "1920,926.27" "1" "1" "0")
(command "_insert" "blkuc6" "1920,925.9" "1" "1" "180")
(command "_insert" "blkuc6" "1920,926.64" "1" "1" "0")
(command "_insert" "blkuc6" "1920,926.27" "1" "1" "180")
(command "_insert" "blkuc6" "1920,927.01" "1" "1" "0")
(command "_insert" "blkuc6" "1920,926.64" "1" "1" "180")
(command "_insert" "blkuc6" "1920,927.38" "1" "1" "0")
(command "_insert" "blkuc6" "1920,927.01" "1" "1" "180")
(command "_insert" "blkuc6" "1920,927.75" "1" "1" "0")
(command "_insert" "blkuc6" "1920,927.38" "1" "1" "180")
(command "_layer" "set" "phccover" "")
(command "_rectangle" "1918.873,933.3" "1921.127,866.7")
(command "_layer" "set" "nitride" "")
(setq phc6 currobj)
(command "_layer" "set" "cover" "")
(command "_rectangle" "1918.873,836.7" "1921.127,963.3")
(command "_layer" "set" "nitride" "")
(command "_layer" "set" "text" "")
(command "_circle" "1917.923,846.7" "0.075")
(command "_circle" "1917.548,846.7" "0.15")
(command "_circle" "1917.173,846.7" "0.075")
(command "_circle" "1916.798,846.7" "0.15")
(command "_circle" "1917.923,848.7" "0.075")
(command "_circle" "1917.548,848.7" "0.075")
(command "_circle" "1917.173,848.7" "0.15")
(command "_circle" "1916.798,848.7" "0.15")
(command "_circle" "1917.923,850.7" "0.075")
(command "_circle" "1917.548,850.7" "0.15")
(command "_circle" "1917.173,850.7" "0.15")
(command "_circle" "1916.798,850.7" "0.15")
(command "_circle" "1917.923,852.7" "0.075")
(command "_circle" "1917.548,852.7" "0.075")
(command "_circle" "1917.173,852.7" "0.075")
(command "_circle" "1916.798,852.7" "0.075")
(command "_circle" "1916.423,852.7" "0.15")
(command "_circle" "1917.923,854.7" "0.075")
(command "_circle" "1917.548,854.7" "0.15")
(command "_circle" "1917.173,854.7" "0.075")
(command "_circle" "1916.798,854.7" "0.075")
(command "_circle" "1916.423,854.7" "0.15")
(command "_circle" "1917.923,856.7" "0.075")
(command "_circle" "1917.548,856.7" "0.075")
(command "_circle" "1917.173,856.7" "0.15")
(command "_circle" "1916.798,856.7" "0.075")
(command "_circle" "1916.423,856.7" "0.15")
(command "_circle" "1917.923,858.7" "0.075")
(command "_circle" "1917.548,858.7" "0.15")
(command "_circle" "1917.173,858.7" "0.15")
(command "_circle" "1916.798,858.7" "0.075")
(command "_circle" "1916.423,858.7" "0.15")
(command "_circle" "1917.923,860.7" "0.075")
(command "_circle" "1917.548,860.7" "0.075")
(command "_circle" "1917.173,860.7" "0.075")
(command "_circle" "1916.798,860.7" "0.15")
(command "_circle" "1916.423,860.7" "0.15")
(command "_circle" "1917.923,862.7" "0.075")
(command "_circle" "1917.548,862.7" "0.15")
(command "_circle" "1917.173,862.7" "0.075")
(command "_circle" "1916.798,862.7" "0.15")
(command "_circle" "1916.423,862.7" "0.15")
(command "_circle" "1917.923,864.7" "0.075")
(command "_circle" "1917.548,864.7" "0.075")
(command "_circle" "1917.173,864.7" "0.15")
(command "_circle" "1916.798,864.7" "0.15")
(command "_circle" "1916.423,864.7" "0.15")
(command "_circle" "1917.923,866.7" "0.075")
(command "_circle" "1917.548,866.7" "0.15")
(command "_circle" "1917.173,866.7" "0.15")
(command "_circle" "1916.798,866.7" "0.15")
(command "_circle" "1916.423,866.7" "0.15")
(command "_circle" "1917.923,868.7" "0.075")
(command "_circle" "1917.548,868.7" "0.075")
(command "_circle" "1917.173,868.7" "0.075")
(command "_circle" "1916.798,868.7" "0.075")
(command "_circle" "1916.423,868.7" "0.075")
(command "_circle" "1916.048,868.7" "0.15")
(command "_circle" "1917.923,870.7" "0.075")
(command "_circle" "1917.548,870.7" "0.15")
(command "_circle" "1917.173,870.7" "0.075")
(command "_circle" "1916.798,870.7" "0.075")
(command "_circle" "1916.423,870.7" "0.075")
(command "_circle" "1916.048,870.7" "0.15")
(command "_circle" "1917.923,872.7" "0.075")
(command "_circle" "1917.548,872.7" "0.075")
(command "_circle" "1917.173,872.7" "0.15")
(command "_circle" "1916.798,872.7" "0.075")
(command "_circle" "1916.423,872.7" "0.075")
(command "_circle" "1916.048,872.7" "0.15")
(command "_circle" "1917.923,874.7" "0.075")
(command "_circle" "1917.548,874.7" "0.15")
(command "_circle" "1917.173,874.7" "0.15")
(command "_circle" "1916.798,874.7" "0.075")
(command "_circle" "1916.423,874.7" "0.075")
(command "_circle" "1916.048,874.7" "0.15")
(command "_circle" "1917.923,876.7" "0.075")
(command "_circle" "1917.548,876.7" "0.075")
(command "_circle" "1917.173,876.7" "0.075")
(command "_circle" "1916.798,876.7" "0.15")
(command "_circle" "1916.423,876.7" "0.075")
(command "_circle" "1916.048,876.7" "0.15")
(command "_circle" "1917.923,878.7" "0.075")
(command "_circle" "1917.548,878.7" "0.15")
(command "_circle" "1917.173,878.7" "0.075")
(command "_circle" "1916.798,878.7" "0.15")
(command "_circle" "1916.423,878.7" "0.075")
(command "_circle" "1916.048,878.7" "0.15")
(command "_circle" "1917.923,880.7" "0.075")
(command "_circle" "1917.548,880.7" "0.075")
(command "_circle" "1917.173,880.7" "0.15")
(command "_circle" "1916.798,880.7" "0.15")
(command "_circle" "1916.423,880.7" "0.075")
(command "_circle" "1916.048,880.7" "0.15")
(command "_circle" "1917.923,882.7" "0.075")
(command "_circle" "1917.548,882.7" "0.15")
(command "_circle" "1917.173,882.7" "0.15")
(command "_circle" "1916.798,882.7" "0.15")
(command "_circle" "1916.423,882.7" "0.075")
(command "_circle" "1916.048,882.7" "0.15")
(command "_circle" "1917.923,884.7" "0.075")
(command "_circle" "1917.548,884.7" "0.075")
(command "_circle" "1917.173,884.7" "0.075")
(command "_circle" "1916.798,884.7" "0.075")
(command "_circle" "1916.423,884.7" "0.15")
(command "_circle" "1916.048,884.7" "0.15")
(command "_circle" "1917.923,886.7" "0.075")
(command "_circle" "1917.548,886.7" "0.15")
(command "_circle" "1917.173,886.7" "0.075")
(command "_circle" "1916.798,886.7" "0.075")
(command "_circle" "1916.423,886.7" "0.15")
(command "_circle" "1916.048,886.7" "0.15")
(command "_circle" "1917.923,888.7" "0.075")
(command "_circle" "1917.548,888.7" "0.075")
(command "_circle" "1917.173,888.7" "0.15")
(command "_circle" "1916.798,888.7" "0.075")
(command "_circle" "1916.423,888.7" "0.15")
(command "_circle" "1916.048,888.7" "0.15")
(command "_circle" "1917.923,890.7" "0.075")
(command "_circle" "1917.548,890.7" "0.15")
(command "_circle" "1917.173,890.7" "0.15")
(command "_circle" "1916.798,890.7" "0.075")
(command "_circle" "1916.423,890.7" "0.15")
(command "_circle" "1916.048,890.7" "0.15")
(command "_circle" "1917.923,892.7" "0.075")
(command "_circle" "1917.548,892.7" "0.075")
(command "_circle" "1917.173,892.7" "0.075")
(command "_circle" "1916.798,892.7" "0.15")
(command "_circle" "1916.423,892.7" "0.15")
(command "_circle" "1916.048,892.7" "0.15")
(command "_circle" "1917.923,894.7" "0.075")
(command "_circle" "1917.548,894.7" "0.15")
(command "_circle" "1917.173,894.7" "0.075")
(command "_circle" "1916.798,894.7" "0.15")
(command "_circle" "1916.423,894.7" "0.15")
(command "_circle" "1916.048,894.7" "0.15")
(command "_circle" "1917.923,896.7" "0.075")
(command "_circle" "1917.548,896.7" "0.075")
(command "_circle" "1917.173,896.7" "0.15")
(command "_circle" "1916.798,896.7" "0.15")
(command "_circle" "1916.423,896.7" "0.15")
(command "_circle" "1916.048,896.7" "0.15")
(command "_circle" "1917.923,898.7" "0.075")
(command "_circle" "1917.548,898.7" "0.15")
(command "_circle" "1917.173,898.7" "0.15")
(command "_circle" "1916.798,898.7" "0.15")
(command "_circle" "1916.423,898.7" "0.15")
(command "_circle" "1916.048,898.7" "0.15")
(command "_circle" "1917.923,900.7" "0.075")
(command "_circle" "1917.548,900.7" "0.075")
(command "_circle" "1917.173,900.7" "0.075")
(command "_circle" "1916.798,900.7" "0.075")
(command "_circle" "1916.423,900.7" "0.075")
(command "_circle" "1916.048,900.7" "0.075")
(command "_circle" "1915.673,900.7" "0.15")
(command "_circle" "1917.923,902.7" "0.075")
(command "_circle" "1917.548,902.7" "0.15")
(command "_circle" "1917.173,902.7" "0.075")
(command "_circle" "1916.798,902.7" "0.075")
(command "_circle" "1916.423,902.7" "0.075")
(command "_circle" "1916.048,902.7" "0.075")
(command "_circle" "1915.673,902.7" "0.15")
(command "_circle" "1917.923,904.7" "0.075")
(command "_circle" "1917.548,904.7" "0.075")
(command "_circle" "1917.173,904.7" "0.15")
(command "_circle" "1916.798,904.7" "0.075")
(command "_circle" "1916.423,904.7" "0.075")
(command "_circle" "1916.048,904.7" "0.075")
(command "_circle" "1915.673,904.7" "0.15")
(command "_circle" "1917.923,906.7" "0.075")
(command "_circle" "1917.548,906.7" "0.15")
(command "_circle" "1917.173,906.7" "0.15")
(command "_circle" "1916.798,906.7" "0.075")
(command "_circle" "1916.423,906.7" "0.075")
(command "_circle" "1916.048,906.7" "0.075")
(command "_circle" "1915.673,906.7" "0.15")
(command "_circle" "1917.923,908.7" "0.075")
(command "_circle" "1917.548,908.7" "0.075")
(command "_circle" "1917.173,908.7" "0.075")
(command "_circle" "1916.798,908.7" "0.15")
(command "_circle" "1916.423,908.7" "0.075")
(command "_circle" "1916.048,908.7" "0.075")
(command "_circle" "1915.673,908.7" "0.15")
(command "_circle" "1917.923,910.7" "0.075")
(command "_circle" "1917.548,910.7" "0.15")
(command "_circle" "1917.173,910.7" "0.075")
(command "_circle" "1916.798,910.7" "0.15")
(command "_circle" "1916.423,910.7" "0.075")
(command "_circle" "1916.048,910.7" "0.075")
(command "_circle" "1915.673,910.7" "0.15")
(command "_circle" "1917.923,912.7" "0.075")
(command "_circle" "1917.548,912.7" "0.075")
(command "_circle" "1917.173,912.7" "0.15")
(command "_circle" "1916.798,912.7" "0.15")
(command "_circle" "1916.423,912.7" "0.075")
(command "_circle" "1916.048,912.7" "0.075")
(command "_circle" "1915.673,912.7" "0.15")
(command "_circle" "1917.923,914.7" "0.075")
(command "_circle" "1917.548,914.7" "0.15")
(command "_circle" "1917.173,914.7" "0.15")
(command "_circle" "1916.798,914.7" "0.15")
(command "_circle" "1916.423,914.7" "0.075")
(command "_circle" "1916.048,914.7" "0.075")
(command "_circle" "1915.673,914.7" "0.15")
(command "_circle" "1917.923,916.7" "0.075")
(command "_circle" "1917.548,916.7" "0.075")
(command "_circle" "1917.173,916.7" "0.075")
(command "_circle" "1916.798,916.7" "0.075")
(command "_circle" "1916.423,916.7" "0.15")
(command "_circle" "1916.048,916.7" "0.075")
(command "_circle" "1915.673,916.7" "0.15")
(command "_circle" "1917.923,918.7" "0.075")
(command "_circle" "1917.548,918.7" "0.15")
(command "_circle" "1917.173,918.7" "0.075")
(command "_circle" "1916.798,918.7" "0.075")
(command "_circle" "1916.423,918.7" "0.15")
(command "_circle" "1916.048,918.7" "0.075")
(command "_circle" "1915.673,918.7" "0.15")
(command "_circle" "1917.923,920.7" "0.075")
(command "_circle" "1917.548,920.7" "0.075")
(command "_circle" "1917.173,920.7" "0.15")
(command "_circle" "1916.798,920.7" "0.075")
(command "_circle" "1916.423,920.7" "0.15")
(command "_circle" "1916.048,920.7" "0.075")
(command "_circle" "1915.673,920.7" "0.15")
(command "_circle" "1917.923,922.7" "0.075")
(command "_circle" "1917.548,922.7" "0.15")
(command "_circle" "1917.173,922.7" "0.15")
(command "_circle" "1916.798,922.7" "0.075")
(command "_circle" "1916.423,922.7" "0.15")
(command "_circle" "1916.048,922.7" "0.075")
(command "_circle" "1915.673,922.7" "0.15")
(command "_circle" "1917.923,924.7" "0.075")
(command "_circle" "1917.548,924.7" "0.075")
(command "_circle" "1917.173,924.7" "0.075")
(command "_circle" "1916.798,924.7" "0.15")
(command "_circle" "1916.423,924.7" "0.15")
(command "_circle" "1916.048,924.7" "0.075")
(command "_circle" "1915.673,924.7" "0.15")
(command "_circle" "1917.923,926.7" "0.075")
(command "_circle" "1917.548,926.7" "0.15")
(command "_circle" "1917.173,926.7" "0.075")
(command "_circle" "1916.798,926.7" "0.15")
(command "_circle" "1916.423,926.7" "0.15")
(command "_circle" "1916.048,926.7" "0.075")
(command "_circle" "1915.673,926.7" "0.15")
(command "_circle" "1917.923,928.7" "0.075")
(command "_circle" "1917.548,928.7" "0.075")
(command "_circle" "1917.173,928.7" "0.15")
(command "_circle" "1916.798,928.7" "0.15")
(command "_circle" "1916.423,928.7" "0.15")
(command "_circle" "1916.048,928.7" "0.075")
(command "_circle" "1915.673,928.7" "0.15")
(command "_circle" "1917.923,930.7" "0.075")
(command "_circle" "1917.548,930.7" "0.15")
(command "_circle" "1917.173,930.7" "0.15")
(command "_circle" "1916.798,930.7" "0.15")
(command "_circle" "1916.423,930.7" "0.15")
(command "_circle" "1916.048,930.7" "0.075")
(command "_circle" "1915.673,930.7" "0.15")
(command "_circle" "1917.923,932.7" "0.075")
(command "_circle" "1917.548,932.7" "0.075")
(command "_circle" "1917.173,932.7" "0.075")
(command "_circle" "1916.798,932.7" "0.075")
(command "_circle" "1916.423,932.7" "0.075")
(command "_circle" "1916.048,932.7" "0.15")
(command "_circle" "1915.673,932.7" "0.15")
(command "_circle" "1917.923,934.7" "0.075")
(command "_circle" "1917.548,934.7" "0.15")
(command "_circle" "1917.173,934.7" "0.075")
(command "_circle" "1916.798,934.7" "0.075")
(command "_circle" "1916.423,934.7" "0.075")
(command "_circle" "1916.048,934.7" "0.15")
(command "_circle" "1915.673,934.7" "0.15")
(command "_circle" "1917.923,936.7" "0.075")
(command "_circle" "1917.548,936.7" "0.075")
(command "_circle" "1917.173,936.7" "0.15")
(command "_circle" "1916.798,936.7" "0.075")
(command "_circle" "1916.423,936.7" "0.075")
(command "_circle" "1916.048,936.7" "0.15")
(command "_circle" "1915.673,936.7" "0.15")
(command "_circle" "1917.923,938.7" "0.075")
(command "_circle" "1917.548,938.7" "0.15")
(command "_circle" "1917.173,938.7" "0.15")
(command "_circle" "1916.798,938.7" "0.075")
(command "_circle" "1916.423,938.7" "0.075")
(command "_circle" "1916.048,938.7" "0.15")
(command "_circle" "1915.673,938.7" "0.15")
(command "_circle" "1917.923,940.7" "0.075")
(command "_circle" "1917.548,940.7" "0.075")
(command "_circle" "1917.173,940.7" "0.075")
(command "_circle" "1916.798,940.7" "0.15")
(command "_circle" "1916.423,940.7" "0.075")
(command "_circle" "1916.048,940.7" "0.15")
(command "_circle" "1915.673,940.7" "0.15")
(command "_circle" "1917.923,942.7" "0.075")
(command "_circle" "1917.548,942.7" "0.15")
(command "_circle" "1917.173,942.7" "0.075")
(command "_circle" "1916.798,942.7" "0.15")
(command "_circle" "1916.423,942.7" "0.075")
(command "_circle" "1916.048,942.7" "0.15")
(command "_circle" "1915.673,942.7" "0.15")
(command "_circle" "1917.923,944.7" "0.075")
(command "_circle" "1917.548,944.7" "0.075")
(command "_circle" "1917.173,944.7" "0.15")
(command "_circle" "1916.798,944.7" "0.15")
(command "_circle" "1916.423,944.7" "0.075")
(command "_circle" "1916.048,944.7" "0.15")
(command "_circle" "1915.673,944.7" "0.15")
(command "_circle" "1917.923,946.7" "0.075")
(command "_circle" "1917.548,946.7" "0.15")
(command "_circle" "1917.173,946.7" "0.15")
(command "_circle" "1916.798,946.7" "0.15")
(command "_circle" "1916.423,946.7" "0.075")
(command "_circle" "1916.048,946.7" "0.15")
(command "_circle" "1915.673,946.7" "0.15")
(command "_circle" "1917.923,948.7" "0.075")
(command "_circle" "1917.548,948.7" "0.075")
(command "_circle" "1917.173,948.7" "0.075")
(command "_circle" "1916.798,948.7" "0.075")
(command "_circle" "1916.423,948.7" "0.15")
(command "_circle" "1916.048,948.7" "0.15")
(command "_circle" "1915.673,948.7" "0.15")
(command "_circle" "1917.923,950.7" "0.075")
(command "_circle" "1917.548,950.7" "0.15")
(command "_circle" "1917.173,950.7" "0.075")
(command "_circle" "1916.798,950.7" "0.075")
(command "_circle" "1916.423,950.7" "0.15")
(command "_circle" "1916.048,950.7" "0.15")
(command "_circle" "1915.673,950.7" "0.15")
(command "_circle" "1917.923,952.7" "0.075")
(command "_circle" "1917.548,952.7" "0.075")
(command "_circle" "1917.173,952.7" "0.15")
(command "_circle" "1916.798,952.7" "0.075")
(command "_circle" "1916.423,952.7" "0.15")
(command "_circle" "1916.048,952.7" "0.15")
(command "_circle" "1915.673,952.7" "0.15")
(command "_circle" "1917.923,954.7" "0.075")
(command "_circle" "1917.548,954.7" "0.15")
(command "_circle" "1917.173,954.7" "0.15")
(command "_circle" "1916.798,954.7" "0.075")
(command "_circle" "1916.423,954.7" "0.15")
(command "_circle" "1916.048,954.7" "0.15")
(command "_circle" "1915.673,954.7" "0.15")
(command "_circle" "1917.923,956.7" "0.075")
(command "_circle" "1917.548,956.7" "0.075")
(command "_circle" "1917.173,956.7" "0.075")
(command "_circle" "1916.798,956.7" "0.15")
(command "_circle" "1916.423,956.7" "0.15")
(command "_circle" "1916.048,956.7" "0.15")
(command "_circle" "1915.673,956.7" "0.15")
(command "_circle" "1917.923,958.7" "0.075")
(command "_circle" "1917.548,958.7" "0.15")
(command "_circle" "1917.173,958.7" "0.075")
(command "_circle" "1916.798,958.7" "0.15")
(command "_circle" "1916.423,958.7" "0.15")
(command "_circle" "1916.048,958.7" "0.15")
(command "_circle" "1915.673,958.7" "0.15")
(command "_circle" "1917.923,960.7" "0.075")
(command "_circle" "1917.548,960.7" "0.075")
(command "_circle" "1917.173,960.7" "0.15")
(command "_circle" "1916.798,960.7" "0.15")
(command "_circle" "1916.423,960.7" "0.15")
(command "_circle" "1916.048,960.7" "0.15")
(command "_circle" "1915.673,960.7" "0.15")
(command "_circle" "1917.923,962.7" "0.075")
(command "_circle" "1917.548,962.7" "0.15")
(command "_circle" "1917.173,962.7" "0.15")
(command "_circle" "1916.798,962.7" "0.15")
(command "_circle" "1916.423,962.7" "0.15")
(command "_circle" "1916.048,962.7" "0.15")
(command "_circle" "1915.673,962.7" "0.15")
(command "_layer" "set" "nitride" "")
(command "_layer" "set" "text" "")
(command-s "_text" "1906.873,963.3" "2" "-90" "a = 370 nm" )
(sssetfirst nil (ssget "_L"))
(if (not (numberp (vl-string-search "Mac" (getvar "platform")))) (c:txtexp))
(command "_layer" "set" "nitride" "")
(command "_layer" "set" "text" "")
(command-s "_text" "1903.873,963.3" "2" "-90" "gap = 270 nm" )
(sssetfirst nil (ssget "_L"))
(if (not (numberp (vl-string-search "Mac" (getvar "platform")))) (c:txtexp))
(command "_layer" "set" "nitride" "")
(command "_layer" "set" "text" "")
(command-s "_text" "1900.873,963.3" "2" "-90" "amplitude = 134.5 nm" )
(sssetfirst nil (ssget "_L"))
(if (not (numberp (vl-string-search "Mac" (getvar "platform")))) (c:txtexp))
(command "_layer" "set" "nitride" "")
(command "_layer" "set" "text" "")
(command-s "_text" "1897.873,963.3" "2" "-90" "start width = 280 nm" )
(sssetfirst nil (ssget "_L"))
(if (not (numberp (vl-string-search "Mac" (getvar "platform")))) (c:txtexp))
(command "_layer" "set" "nitride" "")
(command "_layer" "set" "text" "")
(command-s "_text" "1894.873,963.3" "2" "-90" "width = 294 nm" )
(sssetfirst nil (ssget "_L"))
(if (not (numberp (vl-string-search "Mac" (getvar "platform")))) (c:txtexp))
(command "_layer" "set" "nitride" "")
(command "_layer" "set" "text" "")
(command-s "_text" "1891.873,963.3" "2" "-90" "taper: 15" )
(sssetfirst nil (ssget "_L"))
(if (not (numberp (vl-string-search "Mac" (getvar "platform")))) (c:txtexp))
(command "_layer" "set" "nitride" "")
(command "_layer" "set" "text" "")
(command-s "_text" "1888.873,963.3" "2" "-90" "nominal: 150" )
(sssetfirst nil (ssget "_L"))
(if (not (numberp (vl-string-search "Mac" (getvar "platform")))) (c:txtexp))
(command "_layer" "set" "nitride" "")
(command "_layer" "set" "indicators" "")
(setq coords (list 
(list 1840.415 940) 
(list 1840.415 920) 
(list 1820.415 900) 
(list 1840.415 880) 
(list 1840.415 860) 
(list 1840.415 900) 
(list 1840.415 887.0711) 
(list 1827.4861 900) 
(list 1840.415 912.9289) 
(list 1840.415 900)))
(apply 'command (append '("pline") coords '("c")))
(command "._fillet" "radius" "1" "._fillet" "P" (entlast))
(setq coords (list 
(list 1999.585 940) 
(list 1999.585 920) 
(list 2019.585 900) 
(list 1999.585 880) 
(list 1999.585 860) 
(list 1999.585 900) 
(list 1999.585 887.0711) 
(list 2012.5139 900) 
(list 1999.585 912.9289) 
(list 1999.585 900)))
(apply 'command (append '("pline") coords '("c")))
(command "._fillet" "radius" "1" "._fillet" "P" (entlast))
(command "_layer" "set" "holes" "")
(command "_circle" "1838.0629,914.1124" "0.5")
(command "_circle" "1835.7109,911.7603" "0.5")
(command "_circle" "1833.3588,909.4083" "0.5")
(command "_circle" "1831.0067,907.0562" "0.5")
(command "_circle" "1828.6547,904.7041" "0.5")
(command "_circle" "1826.3026,902.3521" "0.5")
(command "_circle" "1823.9505,900" "0.5")
(command "_circle" "1826.3026,897.6479" "0.5")
(command "_circle" "1828.6547,895.2959" "0.5")
(command "_circle" "1831.0067,892.9438" "0.5")
(command "_circle" "1833.3588,890.5917" "0.5")
(command "_circle" "1835.7109,888.2397" "0.5")
(command "_circle" "1838.0629,885.8876" "0.5")
(command "_circle" "2001.9371,914.1124" "0.5")
(command "_circle" "2004.2891,911.7603" "0.5")
(command "_circle" "2006.6412,909.4083" "0.5")
(command "_circle" "2008.9933,907.0562" "0.5")
(command "_circle" "2011.3453,904.7041" "0.5")
(command "_circle" "2013.6974,902.3521" "0.5")
(command "_circle" "2016.0495,900" "0.5")
(command "_circle" "2013.6974,897.6479" "0.5")
(command "_circle" "2011.3453,895.2959" "0.5")
(command "_circle" "2008.9933,892.9438" "0.5")
(command "_circle" "2006.6412,890.5917" "0.5")
(command "_circle" "2004.2891,888.2397" "0.5")
(command "_circle" "2001.9371,885.8876" "0.5")
(command "_layer" "set" "nitride" "")
(command "_block" "blkcoupler6" "1920,900" coupler6 "")
(command "_insert" "blkcoupler6" "1920,900" "1" "1" "0")
(command "_insert" "blkcoupler6" "1920,900" "1" "1" "180")
(command "_block" "blksinglenanobeam6" "1920,900" singlenanobeam6 "")
(command "_insert" "blksinglenanobeam6" "1920,900" "1" "1" "0")
(command "_insert" "blksinglenanobeam6" "1920,900" "1" "1" "180")
(command "_block" "blkanglednodearray6" "1920,900" anglednodearray6 "")
(command "_insert" "blkanglednodearray6" "1920,900" "1" "1" "0")
(command "_insert" "blkanglednodearray6" "1920,900" "1" "1" "180")
(command "_block" "blkcooledsinglenanobeam6" "1920,900" cooledsinglenanobeam6 "")
(command "_insert" "blkcooledsinglenanobeam6" "1920,900" "1" "1" "0")
(command "_insert" "blkcooledsinglenanobeam6" "1920,900" "1" "1" "180")
(command "_block" "blkyjunction6" "1920,900" yjunction6 "")
(command "_insert" "blkyjunction6" "1920,900" "1" "1" "0")
(command "_insert" "blkyjunction6" "1920,900" "1" "1" "180")
; DRAWING BULGING VEE GROOVE
(command "_layer" "set" "vgroove" "")
(setq coords (list 
(list 1845.415 -605) 
(list 1845.415 0) 
(list 1845.415 0) 
(list 1845.415 1800) 
(list 1845.415 1800) 
(list 1845.415 2405) 
(list 1994.585 2405) 
(list 1994.585 1800) 
(list 1994.585 1800) 
(list 1994.585 0) 
(list 1994.585 0) 
(list 1994.585 -605)))
(apply 'command (append '("pline") coords '("c")))
(command "._fillet" "radius" "0" "._fillet" "P" (entlast))
(command "_layer" "set" "window" "")
(command "_rectangle" "1845.415,-1935" "1994.585,-600")
(command "_rectangle" "1845.415,2400" "1994.585,5300")
(command "_layer" "set" "grid" "")
(command "_rectangle" "1846.415,-1934" "1869.9433,-1909.2133")
(command "_array" "last" "" "R" "75" "3" "25.7867" "24.5283")
(command "_rectangle" "1921,-1934" "1944.5283,-1909.2133")
(command "_array" "last" "" "R" "75" "3" "25.7867" "24.5283")
(command "_rectangle" "1846.415,1" "1869.9433,25.7")
(command "_array" "last" "" "R" "70" "3" "25.7" "24.5283")
(command "_rectangle" "1921,1" "1944.5283,25.7")
(command "_array" "last" "" "R" "70" "3" "25.7" "24.5283")
(command "_rectangle" "1846.415,1801" "1869.9433,1825.9185")
(command "_array" "last" "" "R" "135" "3" "25.9185" "24.5283")
(command "_rectangle" "1921,1801" "1944.5283,1825.9185")
(command "_array" "last" "" "R" "135" "3" "25.9185" "24.5283")
(command "_layer" "set" "vgrooveFDA" "")
(command "_rectangle" "1994.585,-2233" "1845.415,-1933")
(command "_layer" "set" "nitride" "")
(command "_layer" "set" "holes" "")
(command "_circle" "1997.085,331.5" "0.5")
(command "_array" "last" "" "R" "379" "1" "3" "2.5")
(command "_circle" "1842.915,331.5" "0.5")
(command "_array" "last" "" "R" "379" "1" "3" "-2.5")
(command "_layer" "set" "nitride" "")
(command "_layer" "set" "window" "")
(command "_layer" "set" "window" "")
(command "_rectangle" "1999.585,0" "2160.415,1800")
(command "._fillet" "radius" "20" "._fillet" "P" (entlast))
(command "_layer" "set" "grid" "")
(command "_rectangle" "2000.585,1" "2022.4179,25.7")
(command "_array" "last" "" "R" "70" "7" "25.7" "22.8329")
(command "_layer" "set" "nitride" "")
; DRAWING REGION LAYER
(command "_layer" "set" "regionLayer6" "")
(command "_rectangle" "1840,-460" "2000,2260")
(command "_layer" "set" "nitride" "")
(setq coupler6 nil)
(setq singlenanobeam6 nil)
(setq anglednodearray6 nil)
(setq cooledsinglenanobeam6 nil)
(setq yjunction6 nil)
; DEVICE #7
(command "_layer" "set" "window" "")
(command "_circle" "2152.915,-415" "5")
(command "_circle" "2152.915,-402.5" "5")
(command "_circle" "2152.915,-390" "5")
(command "_circle" "2152.915,-377.5" "5")
(command "_circle" "2140.415,-415" "5")
(command "_circle" "2140.415,-402.5" "5")
(command "_circle" "2140.415,-390" "5")
(command "_layer" "set" "nitride" "")
(setq currobj nil)
(setq currobj (ssadd))
; DRAWING COUPLER
(setq coords (list 
(list 2240.0645 -415) 
(list 2240.0645 -413) 
(list 2313.585 -413) 
(list 2313.585 -413) 
(list 2313.9677 -413.0761) 
(list 2314.2921 -413.2929) 
(list 2314.5089 -413.6173) 
(list 2314.585 -414) 
(list 2314.585 -411.8) 
(list 2314.585 -411.8) 
(list 2314.5089 -412.1827) 
(list 2314.2921 -412.5071) 
(list 2313.9677 -412.7239) 
(list 2313.585 -412.8) 
(list 2240.0645 -412.8) 
(list 2240.0645 -410.8) 
(list 2239.9355 -410.8) 
(list 2239.9355 -412.8) 
(list 2166.415 -412.8) 
(list 2166.0323 -412.7239) 
(list 2165.7079 -412.5071) 
(list 2165.4911 -412.1827) 
(list 2165.415 -411.8) 
(list 2165.415 -411.8) 
(list 2165.415 -414) 
(list 2165.4911 -413.6173) 
(list 2165.7079 -413.2929) 
(list 2166.0323 -413.0761) 
(list 2166.415 -413) 
(list 2166.415 -413) 
(list 2239.9355 -413) 
(list 2239.9355 -415)))
(apply 'command (append '("pline") coords '("c")))
(setq currobj (ssadd (entlast) currobj))
(command "._fillet" "radius" "0.3" "._fillet" "P" (entlast))
(command "_layer" "set" "holes" "")
(command "_circle" "2240,-412.9" "0.113")
(setq currobj (ssadd (entlast) currobj))
(command "_layer" "set" "nitride" "")
(command "_layer" "set" "text" "")
(command "_circle" "2239.2,-415" "0.075")
(command "_circle" "2239.2,-414.7" "0.075")
(command "_circle" "2239.2,-414.4" "0.075")
(command "_circle" "2238.9,-415" "0.075")
(command "_circle" "2238.9,-414.7" "0.075")
(command "_circle" "2238.9,-414.4" "0.075")
(command "_circle" "2238.6,-415" "0.075")
(command "_circle" "2238.6,-414.7" "0.075")
(command "_circle" "2238.6,-414.4" "0.075")
(command "_layer" "set" "nitride" "")
(command "_layer" "set" "prebias" "")
(command "_rectangle" "2165.415,-414" "2314.585,-411.8")
(setq currobj (ssadd (entlast) currobj))
(command "_rectangle" "2239.9355,-415" "2240.0645,-410.8")
(setq currobj (ssadd (entlast) currobj))
(command "_layer" "set" "nitride" "")
(setq coupler7 currobj)
(setq currobj nil)
(setq currobj (ssadd))
; DRAWING SINGLE NANOBEAM
(setq coords (list 
(list 2240.0645 -410.8) 
(list 2240.0645 -409.1417) 
(list 2240.0645 -407.4833) 
(list 2240.0645 -405.825) 
(list 2240.0645 -404.1667) 
(list 2240.0645 -402.5083) 
(list 2240.0645 -400.85) 
(list 2240.0645 -399.1917) 
(list 2240.0645 -397.5333) 
(list 2240.0646 -395.875) 
(list 2240.0646 -394.2167) 
(list 2240.0646 -392.5583) 
(list 2240.0646 -390.9) 
(list 2240.0647 -389.2417) 
(list 2240.0647 -387.5833) 
(list 2240.0647 -385.925) 
(list 2240.0648 -384.2667) 
(list 2240.0648 -382.6083) 
(list 2240.0649 -380.95) 
(list 2240.065 -379.2917) 
(list 2240.0651 -377.6333) 
(list 2240.0651 -375.975) 
(list 2240.0652 -374.3167) 
(list 2240.0653 -372.6583) 
(list 2240.0655 -371) 
(list 2240.0656 -369.3417) 
(list 2240.0657 -367.6833) 
(list 2240.0659 -366.025) 
(list 2240.066 -364.3667) 
(list 2240.0662 -362.7083) 
(list 2240.0664 -361.05) 
(list 2240.0666 -359.3917) 
(list 2240.0668 -357.7333) 
(list 2240.067 -356.075) 
(list 2240.0672 -354.4167) 
(list 2240.0675 -352.7583) 
(list 2240.0678 -351.1) 
(list 2240.068 -349.4417) 
(list 2240.0683 -347.7833) 
(list 2240.0686 -346.125) 
(list 2240.069 -344.4667) 
(list 2240.0693 -342.8083) 
(list 2240.0697 -341.15) 
(list 2240.07 -339.4917) 
(list 2240.0704 -337.8333) 
(list 2240.0709 -336.175) 
(list 2240.0713 -334.5167) 
(list 2240.0717 -332.8583) 
(list 2240.0722 -331.2) 
(list 2240.0727 -329.5417) 
(list 2240.0732 -327.8833) 
(list 2240.0738 -326.225) 
(list 2240.0743 -324.5667) 
(list 2240.0749 -322.9083) 
(list 2240.0755 -321.25) 
(list 2240.0761 -319.5917) 
(list 2240.0767 -317.9333) 
(list 2240.0774 -316.275) 
(list 2240.0781 -314.6167) 
(list 2240.0788 -312.9583) 
(list 2240.0796 -311.3) 
(list 2240.0803 -309.6417) 
(list 2240.0811 -307.9833) 
(list 2240.0819 -306.325) 
(list 2240.0828 -304.6667) 
(list 2240.0837 -303.0083) 
(list 2240.0845 -301.35) 
(list 2240.0855 -299.6917) 
(list 2240.0864 -298.0333) 
(list 2240.0874 -296.375) 
(list 2240.0884 -294.7167) 
(list 2240.0895 -293.0583) 
(list 2240.0905 -291.4) 
(list 2240.0916 -289.7417) 
(list 2240.0928 -288.0833) 
(list 2240.0939 -286.425) 
(list 2240.0951 -284.7667) 
(list 2240.0963 -283.1083) 
(list 2240.0976 -281.45) 
(list 2240.0989 -279.7917) 
(list 2240.1002 -278.1333) 
(list 2240.1016 -276.475) 
(list 2240.1029 -274.8167) 
(list 2240.1044 -273.1583) 
(list 2240.1058 -271.5) 
(list 2240.1073 -269.8417) 
(list 2240.1089 -268.1833) 
(list 2240.1104 -266.525) 
(list 2240.112 -264.8667) 
(list 2240.1137 -263.2083) 
(list 2240.1153 -261.55) 
(list 2240.117 -259.8917) 
(list 2240.1188 -258.2333) 
(list 2240.1206 -256.575) 
(list 2240.1224 -254.9167) 
(list 2240.1243 -253.2583) 
(list 2240.1262 -251.6) 
(list 2240.1281 -249.9417) 
(list 2240.1301 -248.2833) 
(list 2240.1322 -246.625) 
(list 2240.1342 -244.9667) 
(list 2240.1363 -243.3083) 
(list 2240.1385 -241.65) 
(list 2240.1407 -239.9917) 
(list 2240.1429 -238.3333) 
(list 2240.1452 -236.675) 
(list 2240.1476 -235.0167) 
(list 2240.1499 -233.3583) 
(list 2240.1523 -231.7) 
(list 2240.1548 -230.0417) 
(list 2240.1573 -228.3833) 
(list 2240.1599 -226.725) 
(list 2240.1625 -225.0667) 
(list 2240.1651 -223.4083) 
(list 2240.1678 -221.75) 
(list 2240.1706 -220.0917) 
(list 2240.1733 -218.4333) 
(list 2240.1762 -216.775) 
(list 2240.1791 -215.1167) 
(list 2240.182 -213.4583) 
(list 2240.185 -211.8) 
(list 2239.815 -211.8) 
(list 2239.818 -213.4583) 
(list 2239.8209 -215.1167) 
(list 2239.8238 -216.775) 
(list 2239.8267 -218.4333) 
(list 2239.8294 -220.0917) 
(list 2239.8322 -221.75) 
(list 2239.8349 -223.4083) 
(list 2239.8375 -225.0667) 
(list 2239.8401 -226.725) 
(list 2239.8427 -228.3833) 
(list 2239.8452 -230.0417) 
(list 2239.8477 -231.7) 
(list 2239.8501 -233.3583) 
(list 2239.8524 -235.0167) 
(list 2239.8548 -236.675) 
(list 2239.8571 -238.3333) 
(list 2239.8593 -239.9917) 
(list 2239.8615 -241.65) 
(list 2239.8637 -243.3083) 
(list 2239.8658 -244.9667) 
(list 2239.8678 -246.625) 
(list 2239.8699 -248.2833) 
(list 2239.8719 -249.9417) 
(list 2239.8738 -251.6) 
(list 2239.8757 -253.2583) 
(list 2239.8776 -254.9167) 
(list 2239.8794 -256.575) 
(list 2239.8812 -258.2333) 
(list 2239.883 -259.8917) 
(list 2239.8847 -261.55) 
(list 2239.8863 -263.2083) 
(list 2239.888 -264.8667) 
(list 2239.8896 -266.525) 
(list 2239.8911 -268.1833) 
(list 2239.8927 -269.8417) 
(list 2239.8942 -271.5) 
(list 2239.8956 -273.1583) 
(list 2239.8971 -274.8167) 
(list 2239.8984 -276.475) 
(list 2239.8998 -278.1333) 
(list 2239.9011 -279.7917) 
(list 2239.9024 -281.45) 
(list 2239.9037 -283.1083) 
(list 2239.9049 -284.7667) 
(list 2239.9061 -286.425) 
(list 2239.9072 -288.0833) 
(list 2239.9084 -289.7417) 
(list 2239.9095 -291.4) 
(list 2239.9105 -293.0583) 
(list 2239.9116 -294.7167) 
(list 2239.9126 -296.375) 
(list 2239.9136 -298.0333) 
(list 2239.9145 -299.6917) 
(list 2239.9155 -301.35) 
(list 2239.9163 -303.0083) 
(list 2239.9172 -304.6667) 
(list 2239.9181 -306.325) 
(list 2239.9189 -307.9833) 
(list 2239.9197 -309.6417) 
(list 2239.9204 -311.3) 
(list 2239.9212 -312.9583) 
(list 2239.9219 -314.6167) 
(list 2239.9226 -316.275) 
(list 2239.9233 -317.9333) 
(list 2239.9239 -319.5917) 
(list 2239.9245 -321.25) 
(list 2239.9251 -322.9083) 
(list 2239.9257 -324.5667) 
(list 2239.9262 -326.225) 
(list 2239.9268 -327.8833) 
(list 2239.9273 -329.5417) 
(list 2239.9278 -331.2) 
(list 2239.9283 -332.8583) 
(list 2239.9287 -334.5167) 
(list 2239.9291 -336.175) 
(list 2239.9296 -337.8333) 
(list 2239.93 -339.4917) 
(list 2239.9303 -341.15) 
(list 2239.9307 -342.8083) 
(list 2239.931 -344.4667) 
(list 2239.9314 -346.125) 
(list 2239.9317 -347.7833) 
(list 2239.932 -349.4417) 
(list 2239.9322 -351.1) 
(list 2239.9325 -352.7583) 
(list 2239.9328 -354.4167) 
(list 2239.933 -356.075) 
(list 2239.9332 -357.7333) 
(list 2239.9334 -359.3917) 
(list 2239.9336 -361.05) 
(list 2239.9338 -362.7083) 
(list 2239.934 -364.3667) 
(list 2239.9341 -366.025) 
(list 2239.9343 -367.6833) 
(list 2239.9344 -369.3417) 
(list 2239.9345 -371) 
(list 2239.9347 -372.6583) 
(list 2239.9348 -374.3167) 
(list 2239.9349 -375.975) 
(list 2239.9349 -377.6333) 
(list 2239.935 -379.2917) 
(list 2239.9351 -380.95) 
(list 2239.9352 -382.6083) 
(list 2239.9352 -384.2667) 
(list 2239.9353 -385.925) 
(list 2239.9353 -387.5833) 
(list 2239.9353 -389.2417) 
(list 2239.9354 -390.9) 
(list 2239.9354 -392.5583) 
(list 2239.9354 -394.2167) 
(list 2239.9354 -395.875) 
(list 2239.9355 -397.5333) 
(list 2239.9355 -399.1917) 
(list 2239.9355 -400.85) 
(list 2239.9355 -402.5083) 
(list 2239.9355 -404.1667) 
(list 2239.9355 -405.825) 
(list 2239.9355 -407.4833) 
(list 2239.9355 -409.1417) 
(list 2239.9355 -410.8)))
(apply 'command (append '("pline") coords '("c")))
(setq currobj (ssadd (entlast) currobj))
(command "_layer" "set" "prebias" "")
(command "_rectangle" "2239.815,-410.8" "2240.185,-211.8")
(setq currobj (ssadd (entlast) currobj))
(command "_layer" "set" "nitride" "")
(setq singlenanobeam7 currobj)
(setq currobj nil)
(setq currobj (ssadd))
; DRAWING NODE ARRAY
(setq coords (list 
(list 2240.185 -211.8) 
(list 2240.5625 -201.8) 
(list 2240.5625 -201.8) 
(list 2240.5625 -200.8) 
(list 2314.585 -212.6864) 
(list 2314.585 -207.7434) 
(list 2240.5625 -197.357) 
(list 2240.5625 -196.357) 
(list 2240.5625 -196.357) 
(list 2240.2625 -186.357) 
(list 2239.7375 -186.357) 
(list 2239.4375 -196.357) 
(list 2239.4375 -196.357) 
(list 2239.4375 -197.357) 
(list 2165.415 -207.7434) 
(list 2165.415 -212.6864) 
(list 2239.4375 -200.8) 
(list 2239.4375 -201.8) 
(list 2239.4375 -201.8) 
(list 2239.815 -211.8)))
(apply 'command (append '("pline") coords '("c")))
(setq currobj (ssadd (entlast) currobj))
(command "_layer" "set" "prebias" "")
(setq coords (list 
(list 2239.4375 -212.6864) 
(list 2239.4375 -200.8) 
(list 2165.415 -212.6864) 
(list 2165.415 -207.7434) 
(list 2239.4375 -197.357) 
(list 2239.4375 -186.357) 
(list 2240.5625 -186.357) 
(list 2240.5625 -197.357) 
(list 2314.585 -207.7434) 
(list 2314.585 -212.6864) 
(list 2240.5625 -200.8) 
(list 2240.5625 -212.6864)))
(apply 'command (append '("pline") coords '("c")))
(setq currobj (ssadd (entlast) currobj))
(command "_layer" "set" "nitride" "")
(command "_layer" "set" "fda1" "")
(setq coords (list 
(list 2240.5625 -200.657) 
(list 2314.585 -212.5434) 
(list 2314.585 -212.3664) 
(list 2240.5625 -200.58)))
(apply 'command (append '("pline") coords '("c")))
(setq currobj (ssadd (entlast) currobj))
(setq coords (list 
(list 2240.5625 -200.437) 
(list 2314.585 -212.2234) 
(list 2314.585 -212.0464) 
(list 2240.5625 -200.36)))
(apply 'command (append '("pline") coords '("c")))
(setq currobj (ssadd (entlast) currobj))
(setq coords (list 
(list 2240.5625 -200.217) 
(list 2314.585 -211.9034) 
(list 2314.585 -211.7264) 
(list 2240.5625 -200.14)))
(apply 'command (append '("pline") coords '("c")))
(setq currobj (ssadd (entlast) currobj))
(setq coords (list 
(list 2240.5625 -199.997) 
(list 2314.585 -211.5834) 
(list 2314.585 -211.4064) 
(list 2240.5625 -199.92)))
(apply 'command (append '("pline") coords '("c")))
(setq currobj (ssadd (entlast) currobj))
(setq coords (list 
(list 2240.5625 -199.777) 
(list 2314.585 -211.2634) 
(list 2314.585 -211.0864) 
(list 2240.5625 -199.7)))
(apply 'command (append '("pline") coords '("c")))
(setq currobj (ssadd (entlast) currobj))
(setq coords (list 
(list 2240.5625 -199.557) 
(list 2314.585 -210.9434) 
(list 2314.585 -210.7664) 
(list 2240.5625 -199.48)))
(apply 'command (append '("pline") coords '("c")))
(setq currobj (ssadd (entlast) currobj))
(setq coords (list 
(list 2240.5625 -199.337) 
(list 2314.585 -210.6234) 
(list 2314.585 -210.4464) 
(list 2240.5625 -199.26)))
(apply 'command (append '("pline") coords '("c")))
(setq currobj (ssadd (entlast) currobj))
(setq coords (list 
(list 2240.5625 -199.117) 
(list 2314.585 -210.3034) 
(list 2314.585 -210.1264) 
(list 2240.5625 -199.04)))
(apply 'command (append '("pline") coords '("c")))
(setq currobj (ssadd (entlast) currobj))
(setq coords (list 
(list 2240.5625 -198.897) 
(list 2314.585 -209.9834) 
(list 2314.585 -209.8064) 
(list 2240.5625 -198.82)))
(apply 'command (append '("pline") coords '("c")))
(setq currobj (ssadd (entlast) currobj))
(setq coords (list 
(list 2240.5625 -198.677) 
(list 2314.585 -209.6634) 
(list 2314.585 -209.4864) 
(list 2240.5625 -198.6)))
(apply 'command (append '("pline") coords '("c")))
(setq currobj (ssadd (entlast) currobj))
(setq coords (list 
(list 2240.5625 -198.457) 
(list 2314.585 -209.3434) 
(list 2314.585 -209.1664) 
(list 2240.5625 -198.38)))
(apply 'command (append '("pline") coords '("c")))
(setq currobj (ssadd (entlast) currobj))
(setq coords (list 
(list 2240.5625 -198.237) 
(list 2314.585 -209.0234) 
(list 2314.585 -208.8464) 
(list 2240.5625 -198.16)))
(apply 'command (append '("pline") coords '("c")))
(setq currobj (ssadd (entlast) currobj))
(setq coords (list 
(list 2240.5625 -198.017) 
(list 2314.585 -208.7034) 
(list 2314.585 -208.5264) 
(list 2240.5625 -197.94)))
(apply 'command (append '("pline") coords '("c")))
(setq currobj (ssadd (entlast) currobj))
(setq coords (list 
(list 2240.5625 -197.797) 
(list 2314.585 -208.3834) 
(list 2314.585 -208.2064) 
(list 2240.5625 -197.72)))
(apply 'command (append '("pline") coords '("c")))
(setq currobj (ssadd (entlast) currobj))
(setq coords (list 
(list 2240.5625 -197.577) 
(list 2314.585 -208.0634) 
(list 2314.585 -207.8864) 
(list 2240.5625 -197.5)))
(apply 'command (append '("pline") coords '("c")))
(setq currobj (ssadd (entlast) currobj))
(setq coords (list 
(list 2239.4375 -197.5) 
(list 2165.415 -207.8864) 
(list 2165.415 -208.0634) 
(list 2239.4375 -197.577)))
(apply 'command (append '("pline") coords '("c")))
(setq currobj (ssadd (entlast) currobj))
(setq coords (list 
(list 2239.4375 -197.72) 
(list 2165.415 -208.2064) 
(list 2165.415 -208.3834) 
(list 2239.4375 -197.797)))
(apply 'command (append '("pline") coords '("c")))
(setq currobj (ssadd (entlast) currobj))
(setq coords (list 
(list 2239.4375 -197.94) 
(list 2165.415 -208.5264) 
(list 2165.415 -208.7034) 
(list 2239.4375 -198.017)))
(apply 'command (append '("pline") coords '("c")))
(setq currobj (ssadd (entlast) currobj))
(setq coords (list 
(list 2239.4375 -198.16) 
(list 2165.415 -208.8464) 
(list 2165.415 -209.0234) 
(list 2239.4375 -198.237)))
(apply 'command (append '("pline") coords '("c")))
(setq currobj (ssadd (entlast) currobj))
(setq coords (list 
(list 2239.4375 -198.38) 
(list 2165.415 -209.1664) 
(list 2165.415 -209.3434) 
(list 2239.4375 -198.457)))
(apply 'command (append '("pline") coords '("c")))
(setq currobj (ssadd (entlast) currobj))
(setq coords (list 
(list 2239.4375 -198.6) 
(list 2165.415 -209.4864) 
(list 2165.415 -209.6634) 
(list 2239.4375 -198.677)))
(apply 'command (append '("pline") coords '("c")))
(setq currobj (ssadd (entlast) currobj))
(setq coords (list 
(list 2239.4375 -198.82) 
(list 2165.415 -209.8064) 
(list 2165.415 -209.9834) 
(list 2239.4375 -198.897)))
(apply 'command (append '("pline") coords '("c")))
(setq currobj (ssadd (entlast) currobj))
(setq coords (list 
(list 2239.4375 -199.04) 
(list 2165.415 -210.1264) 
(list 2165.415 -210.3034) 
(list 2239.4375 -199.117)))
(apply 'command (append '("pline") coords '("c")))
(setq currobj (ssadd (entlast) currobj))
(setq coords (list 
(list 2239.4375 -199.26) 
(list 2165.415 -210.4464) 
(list 2165.415 -210.6234) 
(list 2239.4375 -199.337)))
(apply 'command (append '("pline") coords '("c")))
(setq currobj (ssadd (entlast) currobj))
(setq coords (list 
(list 2239.4375 -199.48) 
(list 2165.415 -210.7664) 
(list 2165.415 -210.9434) 
(list 2239.4375 -199.557)))
(apply 'command (append '("pline") coords '("c")))
(setq currobj (ssadd (entlast) currobj))
(setq coords (list 
(list 2239.4375 -199.7) 
(list 2165.415 -211.0864) 
(list 2165.415 -211.2634) 
(list 2239.4375 -199.777)))
(apply 'command (append '("pline") coords '("c")))
(setq currobj (ssadd (entlast) currobj))
(setq coords (list 
(list 2239.4375 -199.92) 
(list 2165.415 -211.4064) 
(list 2165.415 -211.5834) 
(list 2239.4375 -199.997)))
(apply 'command (append '("pline") coords '("c")))
(setq currobj (ssadd (entlast) currobj))
(setq coords (list 
(list 2239.4375 -200.14) 
(list 2165.415 -211.7264) 
(list 2165.415 -211.9034) 
(list 2239.4375 -200.217)))
(apply 'command (append '("pline") coords '("c")))
(setq currobj (ssadd (entlast) currobj))
(setq coords (list 
(list 2239.4375 -200.36) 
(list 2165.415 -212.0464) 
(list 2165.415 -212.2234) 
(list 2239.4375 -200.437)))
(apply 'command (append '("pline") coords '("c")))
(setq currobj (ssadd (entlast) currobj))
(setq coords (list 
(list 2239.4375 -200.58) 
(list 2165.415 -212.3664) 
(list 2165.415 -212.5434) 
(list 2239.4375 -200.657)))
(apply 'command (append '("pline") coords '("c")))
(setq currobj (ssadd (entlast) currobj))
(command "_layer" "set" "nitride" "")
(command "_layer" "set" "text" "")
(command "_circle" "2238.985,-211.8" "0.075")
(command "_circle" "2238.985,-211.5" "0.075")
(command "_circle" "2238.985,-211.2" "0.075")
(command "_circle" "2238.985,-210.9" "0.075")
(command "_circle" "2238.985,-210.6" "0.075")
(command "_circle" "2238.685,-211.8" "0.075")
(command "_circle" "2238.685,-211.5" "0.075")
(command "_circle" "2238.685,-211.2" "0.075")
(command "_circle" "2238.685,-210.9" "0.075")
(command "_circle" "2238.685,-210.6" "0.075")
(command "_circle" "2238.385,-211.8" "0.075")
(command "_circle" "2238.385,-211.5" "0.075")
(command "_circle" "2238.385,-211.2" "0.075")
(command "_circle" "2238.385,-210.9" "0.075")
(command "_circle" "2238.385,-210.6" "0.075")
(command "_circle" "2238.085,-211.8" "0.075")
(command "_circle" "2238.085,-211.5" "0.075")
(command "_circle" "2238.085,-211.2" "0.075")
(command "_circle" "2238.085,-210.9" "0.075")
(command "_circle" "2238.085,-210.6" "0.075")
(command "_circle" "2237.785,-211.8" "0.075")
(command "_circle" "2237.785,-211.5" "0.075")
(command "_circle" "2237.785,-211.2" "0.075")
(command "_circle" "2237.785,-210.9" "0.075")
(command "_circle" "2237.785,-210.6" "0.075")
(command "_layer" "set" "nitride" "")
(setq anglednodearray7 currobj)
(setq currobj nil)
(setq currobj (ssadd))
; DRAWING COOLED SINGLE NANOBEAM
(setq coords (list 
(list 2240.2625 -186.357) 
(list 2240.2625 -181.357) 
(list 2239.7375 -181.357) 
(list 2239.7375 -186.357)))
(apply 'command (append '("pline") coords '("c")))
(setq currobj (ssadd (entlast) currobj))
(command "_layer" "set" "prebias" "")
(command "_rectangle" "2239.7375,-186.357" "2240.2625,-181.357")
(setq currobj (ssadd (entlast) currobj))
(command "_layer" "set" "nitride" "")
(setq coords (list 
(list 2240.2625 -181.357) 
(list 2240.5625 -171.357) 
(list 2240.5625 -171.357) 
(list 2240.5625 -170.357) 
(list 2314.585 -171.107) 
(list 2314.585 -166.164) 
(list 2240.5625 -166.914) 
(list 2240.5625 -165.914) 
(list 2240.5625 -165.914) 
(list 2240.2625 -155.914) 
(list 2239.7375 -155.914) 
(list 2239.4375 -165.914) 
(list 2239.4375 -165.914) 
(list 2239.4375 -166.914) 
(list 2165.415 -166.164) 
(list 2165.415 -171.107) 
(list 2239.4375 -170.357) 
(list 2239.4375 -171.357) 
(list 2239.4375 -171.357) 
(list 2239.7375 -181.357)))
(apply 'command (append '("pline") coords '("c")))
(setq currobj (ssadd (entlast) currobj))
(command "_layer" "set" "prebias" "")
(setq coords (list 
(list 2239.4375 -181.357) 
(list 2239.4375 -170.357) 
(list 2165.415 -171.107) 
(list 2165.415 -166.164) 
(list 2239.4375 -166.914) 
(list 2239.4375 -155.914) 
(list 2240.5625 -155.914) 
(list 2240.5625 -166.914) 
(list 2314.585 -166.164) 
(list 2314.585 -171.107) 
(list 2240.5625 -170.357) 
(list 2240.5625 -181.357)))
(apply 'command (append '("pline") coords '("c")))
(setq currobj (ssadd (entlast) currobj))
(command "_layer" "set" "nitride" "")
(command "_layer" "set" "fda1" "")
(setq coords (list 
(list 2240.5625 -170.214) 
(list 2314.585 -170.964) 
(list 2314.585 -170.787) 
(list 2240.5625 -170.137)))
(apply 'command (append '("pline") coords '("c")))
(setq currobj (ssadd (entlast) currobj))
(setq coords (list 
(list 2240.5625 -169.994) 
(list 2314.585 -170.644) 
(list 2314.585 -170.467) 
(list 2240.5625 -169.917)))
(apply 'command (append '("pline") coords '("c")))
(setq currobj (ssadd (entlast) currobj))
(setq coords (list 
(list 2240.5625 -169.774) 
(list 2314.585 -170.324) 
(list 2314.585 -170.147) 
(list 2240.5625 -169.697)))
(apply 'command (append '("pline") coords '("c")))
(setq currobj (ssadd (entlast) currobj))
(setq coords (list 
(list 2240.5625 -169.554) 
(list 2314.585 -170.004) 
(list 2314.585 -169.827) 
(list 2240.5625 -169.477)))
(apply 'command (append '("pline") coords '("c")))
(setq currobj (ssadd (entlast) currobj))
(setq coords (list 
(list 2240.5625 -169.334) 
(list 2314.585 -169.684) 
(list 2314.585 -169.507) 
(list 2240.5625 -169.257)))
(apply 'command (append '("pline") coords '("c")))
(setq currobj (ssadd (entlast) currobj))
(setq coords (list 
(list 2240.5625 -169.114) 
(list 2314.585 -169.364) 
(list 2314.585 -169.187) 
(list 2240.5625 -169.037)))
(apply 'command (append '("pline") coords '("c")))
(setq currobj (ssadd (entlast) currobj))
(setq coords (list 
(list 2240.5625 -168.894) 
(list 2314.585 -169.044) 
(list 2314.585 -168.867) 
(list 2240.5625 -168.817)))
(apply 'command (append '("pline") coords '("c")))
(setq currobj (ssadd (entlast) currobj))
(setq coords (list 
(list 2240.5625 -168.674) 
(list 2314.585 -168.724) 
(list 2314.585 -168.547) 
(list 2240.5625 -168.597)))
(apply 'command (append '("pline") coords '("c")))
(setq currobj (ssadd (entlast) currobj))
(setq coords (list 
(list 2240.5625 -168.454) 
(list 2314.585 -168.404) 
(list 2314.585 -168.227) 
(list 2240.5625 -168.377)))
(apply 'command (append '("pline") coords '("c")))
(setq currobj (ssadd (entlast) currobj))
(setq coords (list 
(list 2240.5625 -168.234) 
(list 2314.585 -168.084) 
(list 2314.585 -167.907) 
(list 2240.5625 -168.157)))
(apply 'command (append '("pline") coords '("c")))
(setq currobj (ssadd (entlast) currobj))
(setq coords (list 
(list 2240.5625 -168.014) 
(list 2314.585 -167.764) 
(list 2314.585 -167.587) 
(list 2240.5625 -167.937)))
(apply 'command (append '("pline") coords '("c")))
(setq currobj (ssadd (entlast) currobj))
(setq coords (list 
(list 2240.5625 -167.794) 
(list 2314.585 -167.444) 
(list 2314.585 -167.267) 
(list 2240.5625 -167.717)))
(apply 'command (append '("pline") coords '("c")))
(setq currobj (ssadd (entlast) currobj))
(setq coords (list 
(list 2240.5625 -167.574) 
(list 2314.585 -167.124) 
(list 2314.585 -166.947) 
(list 2240.5625 -167.497)))
(apply 'command (append '("pline") coords '("c")))
(setq currobj (ssadd (entlast) currobj))
(setq coords (list 
(list 2240.5625 -167.354) 
(list 2314.585 -166.804) 
(list 2314.585 -166.627) 
(list 2240.5625 -167.277)))
(apply 'command (append '("pline") coords '("c")))
(setq currobj (ssadd (entlast) currobj))
(setq coords (list 
(list 2240.5625 -167.134) 
(list 2314.585 -166.484) 
(list 2314.585 -166.307) 
(list 2240.5625 -167.057)))
(apply 'command (append '("pline") coords '("c")))
(setq currobj (ssadd (entlast) currobj))
(setq coords (list 
(list 2239.4375 -167.057) 
(list 2165.415 -166.307) 
(list 2165.415 -166.484) 
(list 2239.4375 -167.134)))
(apply 'command (append '("pline") coords '("c")))
(setq currobj (ssadd (entlast) currobj))
(setq coords (list 
(list 2239.4375 -167.277) 
(list 2165.415 -166.627) 
(list 2165.415 -166.804) 
(list 2239.4375 -167.354)))
(apply 'command (append '("pline") coords '("c")))
(setq currobj (ssadd (entlast) currobj))
(setq coords (list 
(list 2239.4375 -167.497) 
(list 2165.415 -166.947) 
(list 2165.415 -167.124) 
(list 2239.4375 -167.574)))
(apply 'command (append '("pline") coords '("c")))
(setq currobj (ssadd (entlast) currobj))
(setq coords (list 
(list 2239.4375 -167.717) 
(list 2165.415 -167.267) 
(list 2165.415 -167.444) 
(list 2239.4375 -167.794)))
(apply 'command (append '("pline") coords '("c")))
(setq currobj (ssadd (entlast) currobj))
(setq coords (list 
(list 2239.4375 -167.937) 
(list 2165.415 -167.587) 
(list 2165.415 -167.764) 
(list 2239.4375 -168.014)))
(apply 'command (append '("pline") coords '("c")))
(setq currobj (ssadd (entlast) currobj))
(setq coords (list 
(list 2239.4375 -168.157) 
(list 2165.415 -167.907) 
(list 2165.415 -168.084) 
(list 2239.4375 -168.234)))
(apply 'command (append '("pline") coords '("c")))
(setq currobj (ssadd (entlast) currobj))
(setq coords (list 
(list 2239.4375 -168.377) 
(list 2165.415 -168.227) 
(list 2165.415 -168.404) 
(list 2239.4375 -168.454)))
(apply 'command (append '("pline") coords '("c")))
(setq currobj (ssadd (entlast) currobj))
(setq coords (list 
(list 2239.4375 -168.597) 
(list 2165.415 -168.547) 
(list 2165.415 -168.724) 
(list 2239.4375 -168.674)))
(apply 'command (append '("pline") coords '("c")))
(setq currobj (ssadd (entlast) currobj))
(setq coords (list 
(list 2239.4375 -168.817) 
(list 2165.415 -168.867) 
(list 2165.415 -169.044) 
(list 2239.4375 -168.894)))
(apply 'command (append '("pline") coords '("c")))
(setq currobj (ssadd (entlast) currobj))
(setq coords (list 
(list 2239.4375 -169.037) 
(list 2165.415 -169.187) 
(list 2165.415 -169.364) 
(list 2239.4375 -169.114)))
(apply 'command (append '("pline") coords '("c")))
(setq currobj (ssadd (entlast) currobj))
(setq coords (list 
(list 2239.4375 -169.257) 
(list 2165.415 -169.507) 
(list 2165.415 -169.684) 
(list 2239.4375 -169.334)))
(apply 'command (append '("pline") coords '("c")))
(setq currobj (ssadd (entlast) currobj))
(setq coords (list 
(list 2239.4375 -169.477) 
(list 2165.415 -169.827) 
(list 2165.415 -170.004) 
(list 2239.4375 -169.554)))
(apply 'command (append '("pline") coords '("c")))
(setq currobj (ssadd (entlast) currobj))
(setq coords (list 
(list 2239.4375 -169.697) 
(list 2165.415 -170.147) 
(list 2165.415 -170.324) 
(list 2239.4375 -169.774)))
(apply 'command (append '("pline") coords '("c")))
(setq currobj (ssadd (entlast) currobj))
(setq coords (list 
(list 2239.4375 -169.917) 
(list 2165.415 -170.467) 
(list 2165.415 -170.644) 
(list 2239.4375 -169.994)))
(apply 'command (append '("pline") coords '("c")))
(setq currobj (ssadd (entlast) currobj))
(setq coords (list 
(list 2239.4375 -170.137) 
(list 2165.415 -170.787) 
(list 2165.415 -170.964) 
(list 2239.4375 -170.214)))
(apply 'command (append '("pline") coords '("c")))
(setq currobj (ssadd (entlast) currobj))
(command "_layer" "set" "nitride" "")
(command "_layer" "set" "text" "")
(command "_circle" "2239.0625,-181.357" "0.075")
(command "_circle" "2239.0625,-181.057" "0.075")
(command "_circle" "2239.0625,-180.757" "0.075")
(command "_circle" "2239.0625,-180.457" "0.075")
(command "_circle" "2239.0625,-180.157" "0.075")
(command "_circle" "2238.7625,-181.357" "0.075")
(command "_circle" "2238.7625,-181.057" "0.075")
(command "_circle" "2238.7625,-180.757" "0.075")
(command "_circle" "2238.7625,-180.457" "0.075")
(command "_circle" "2238.7625,-180.157" "0.075")
(command "_circle" "2238.4625,-181.357" "0.075")
(command "_circle" "2238.4625,-181.057" "0.075")
(command "_circle" "2238.4625,-180.757" "0.075")
(command "_circle" "2238.4625,-180.457" "0.075")
(command "_circle" "2238.4625,-180.157" "0.075")
(command "_circle" "2238.1625,-181.357" "0.075")
(command "_circle" "2238.1625,-181.057" "0.075")
(command "_circle" "2238.1625,-180.757" "0.075")
(command "_circle" "2238.1625,-180.457" "0.075")
(command "_circle" "2238.1625,-180.157" "0.075")
(command "_circle" "2237.8625,-181.357" "0.075")
(command "_circle" "2237.8625,-181.057" "0.075")
(command "_circle" "2237.8625,-180.757" "0.075")
(command "_circle" "2237.8625,-180.457" "0.075")
(command "_circle" "2237.8625,-180.157" "0.075")
(command "_layer" "set" "nitride" "")
(setq coords (list 
(list 2240.2625 -155.914) 
(list 2240.2625 -40.2693) 
(list 2239.7375 -40.2693) 
(list 2239.7375 -155.914)))
(apply 'command (append '("pline") coords '("c")))
(setq currobj (ssadd (entlast) currobj))
(command "_layer" "set" "prebias" "")
(command "_rectangle" "2239.7375,-155.914" "2240.2625,-40.2693")
(setq currobj (ssadd (entlast) currobj))
(command "_layer" "set" "nitride" "")
(setq coords (list 
(list 2240.2625 -40.2693) 
(list 2240.5625 -30.2693) 
(list 2240.5625 -30.2693) 
(list 2240.5625 -29.2693) 
(list 2314.585 -30.0193) 
(list 2314.585 -25.0763) 
(list 2240.5625 -25.8263) 
(list 2240.5625 -24.8263) 
(list 2240.5625 -24.8263) 
(list 2240.2625 -14.8263) 
(list 2239.7375 -14.8263) 
(list 2239.4375 -24.8263) 
(list 2239.4375 -24.8263) 
(list 2239.4375 -25.8263) 
(list 2165.415 -25.0763) 
(list 2165.415 -30.0193) 
(list 2239.4375 -29.2693) 
(list 2239.4375 -30.2693) 
(list 2239.4375 -30.2693) 
(list 2239.7375 -40.2693)))
(apply 'command (append '("pline") coords '("c")))
(setq currobj (ssadd (entlast) currobj))
(command "_layer" "set" "prebias" "")
(setq coords (list 
(list 2239.4375 -40.2693) 
(list 2239.4375 -29.2693) 
(list 2165.415 -30.0193) 
(list 2165.415 -25.0763) 
(list 2239.4375 -25.8263) 
(list 2239.4375 -14.8263) 
(list 2240.5625 -14.8263) 
(list 2240.5625 -25.8263) 
(list 2314.585 -25.0763) 
(list 2314.585 -30.0193) 
(list 2240.5625 -29.2693) 
(list 2240.5625 -40.2693)))
(apply 'command (append '("pline") coords '("c")))
(setq currobj (ssadd (entlast) currobj))
(command "_layer" "set" "nitride" "")
(command "_layer" "set" "fda1" "")
(setq coords (list 
(list 2240.5625 -29.1263) 
(list 2314.585 -29.8763) 
(list 2314.585 -29.6993) 
(list 2240.5625 -29.0493)))
(apply 'command (append '("pline") coords '("c")))
(setq currobj (ssadd (entlast) currobj))
(setq coords (list 
(list 2240.5625 -28.9063) 
(list 2314.585 -29.5563) 
(list 2314.585 -29.3793) 
(list 2240.5625 -28.8293)))
(apply 'command (append '("pline") coords '("c")))
(setq currobj (ssadd (entlast) currobj))
(setq coords (list 
(list 2240.5625 -28.6863) 
(list 2314.585 -29.2363) 
(list 2314.585 -29.0593) 
(list 2240.5625 -28.6093)))
(apply 'command (append '("pline") coords '("c")))
(setq currobj (ssadd (entlast) currobj))
(setq coords (list 
(list 2240.5625 -28.4663) 
(list 2314.585 -28.9163) 
(list 2314.585 -28.7393) 
(list 2240.5625 -28.3893)))
(apply 'command (append '("pline") coords '("c")))
(setq currobj (ssadd (entlast) currobj))
(setq coords (list 
(list 2240.5625 -28.2463) 
(list 2314.585 -28.5963) 
(list 2314.585 -28.4193) 
(list 2240.5625 -28.1693)))
(apply 'command (append '("pline") coords '("c")))
(setq currobj (ssadd (entlast) currobj))
(setq coords (list 
(list 2240.5625 -28.0263) 
(list 2314.585 -28.2763) 
(list 2314.585 -28.0993) 
(list 2240.5625 -27.9493)))
(apply 'command (append '("pline") coords '("c")))
(setq currobj (ssadd (entlast) currobj))
(setq coords (list 
(list 2240.5625 -27.8063) 
(list 2314.585 -27.9563) 
(list 2314.585 -27.7793) 
(list 2240.5625 -27.7293)))
(apply 'command (append '("pline") coords '("c")))
(setq currobj (ssadd (entlast) currobj))
(setq coords (list 
(list 2240.5625 -27.5863) 
(list 2314.585 -27.6363) 
(list 2314.585 -27.4593) 
(list 2240.5625 -27.5093)))
(apply 'command (append '("pline") coords '("c")))
(setq currobj (ssadd (entlast) currobj))
(setq coords (list 
(list 2240.5625 -27.3663) 
(list 2314.585 -27.3163) 
(list 2314.585 -27.1393) 
(list 2240.5625 -27.2893)))
(apply 'command (append '("pline") coords '("c")))
(setq currobj (ssadd (entlast) currobj))
(setq coords (list 
(list 2240.5625 -27.1463) 
(list 2314.585 -26.9963) 
(list 2314.585 -26.8193) 
(list 2240.5625 -27.0693)))
(apply 'command (append '("pline") coords '("c")))
(setq currobj (ssadd (entlast) currobj))
(setq coords (list 
(list 2240.5625 -26.9263) 
(list 2314.585 -26.6763) 
(list 2314.585 -26.4993) 
(list 2240.5625 -26.8493)))
(apply 'command (append '("pline") coords '("c")))
(setq currobj (ssadd (entlast) currobj))
(setq coords (list 
(list 2240.5625 -26.7063) 
(list 2314.585 -26.3563) 
(list 2314.585 -26.1793) 
(list 2240.5625 -26.6293)))
(apply 'command (append '("pline") coords '("c")))
(setq currobj (ssadd (entlast) currobj))
(setq coords (list 
(list 2240.5625 -26.4863) 
(list 2314.585 -26.0363) 
(list 2314.585 -25.8593) 
(list 2240.5625 -26.4093)))
(apply 'command (append '("pline") coords '("c")))
(setq currobj (ssadd (entlast) currobj))
(setq coords (list 
(list 2240.5625 -26.2663) 
(list 2314.585 -25.7163) 
(list 2314.585 -25.5393) 
(list 2240.5625 -26.1893)))
(apply 'command (append '("pline") coords '("c")))
(setq currobj (ssadd (entlast) currobj))
(setq coords (list 
(list 2240.5625 -26.0463) 
(list 2314.585 -25.3963) 
(list 2314.585 -25.2193) 
(list 2240.5625 -25.9693)))
(apply 'command (append '("pline") coords '("c")))
(setq currobj (ssadd (entlast) currobj))
(setq coords (list 
(list 2239.4375 -25.9693) 
(list 2165.415 -25.2193) 
(list 2165.415 -25.3963) 
(list 2239.4375 -26.0463)))
(apply 'command (append '("pline") coords '("c")))
(setq currobj (ssadd (entlast) currobj))
(setq coords (list 
(list 2239.4375 -26.1893) 
(list 2165.415 -25.5393) 
(list 2165.415 -25.7163) 
(list 2239.4375 -26.2663)))
(apply 'command (append '("pline") coords '("c")))
(setq currobj (ssadd (entlast) currobj))
(setq coords (list 
(list 2239.4375 -26.4093) 
(list 2165.415 -25.8593) 
(list 2165.415 -26.0363) 
(list 2239.4375 -26.4863)))
(apply 'command (append '("pline") coords '("c")))
(setq currobj (ssadd (entlast) currobj))
(setq coords (list 
(list 2239.4375 -26.6293) 
(list 2165.415 -26.1793) 
(list 2165.415 -26.3563) 
(list 2239.4375 -26.7063)))
(apply 'command (append '("pline") coords '("c")))
(setq currobj (ssadd (entlast) currobj))
(setq coords (list 
(list 2239.4375 -26.8493) 
(list 2165.415 -26.4993) 
(list 2165.415 -26.6763) 
(list 2239.4375 -26.9263)))
(apply 'command (append '("pline") coords '("c")))
(setq currobj (ssadd (entlast) currobj))
(setq coords (list 
(list 2239.4375 -27.0693) 
(list 2165.415 -26.8193) 
(list 2165.415 -26.9963) 
(list 2239.4375 -27.1463)))
(apply 'command (append '("pline") coords '("c")))
(setq currobj (ssadd (entlast) currobj))
(setq coords (list 
(list 2239.4375 -27.2893) 
(list 2165.415 -27.1393) 
(list 2165.415 -27.3163) 
(list 2239.4375 -27.3663)))
(apply 'command (append '("pline") coords '("c")))
(setq currobj (ssadd (entlast) currobj))
(setq coords (list 
(list 2239.4375 -27.5093) 
(list 2165.415 -27.4593) 
(list 2165.415 -27.6363) 
(list 2239.4375 -27.5863)))
(apply 'command (append '("pline") coords '("c")))
(setq currobj (ssadd (entlast) currobj))
(setq coords (list 
(list 2239.4375 -27.7293) 
(list 2165.415 -27.7793) 
(list 2165.415 -27.9563) 
(list 2239.4375 -27.8063)))
(apply 'command (append '("pline") coords '("c")))
(setq currobj (ssadd (entlast) currobj))
(setq coords (list 
(list 2239.4375 -27.9493) 
(list 2165.415 -28.0993) 
(list 2165.415 -28.2763) 
(list 2239.4375 -28.0263)))
(apply 'command (append '("pline") coords '("c")))
(setq currobj (ssadd (entlast) currobj))
(setq coords (list 
(list 2239.4375 -28.1693) 
(list 2165.415 -28.4193) 
(list 2165.415 -28.5963) 
(list 2239.4375 -28.2463)))
(apply 'command (append '("pline") coords '("c")))
(setq currobj (ssadd (entlast) currobj))
(setq coords (list 
(list 2239.4375 -28.3893) 
(list 2165.415 -28.7393) 
(list 2165.415 -28.9163) 
(list 2239.4375 -28.4663)))
(apply 'command (append '("pline") coords '("c")))
(setq currobj (ssadd (entlast) currobj))
(setq coords (list 
(list 2239.4375 -28.6093) 
(list 2165.415 -29.0593) 
(list 2165.415 -29.2363) 
(list 2239.4375 -28.6863)))
(apply 'command (append '("pline") coords '("c")))
(setq currobj (ssadd (entlast) currobj))
(setq coords (list 
(list 2239.4375 -28.8293) 
(list 2165.415 -29.3793) 
(list 2165.415 -29.5563) 
(list 2239.4375 -28.9063)))
(apply 'command (append '("pline") coords '("c")))
(setq currobj (ssadd (entlast) currobj))
(setq coords (list 
(list 2239.4375 -29.0493) 
(list 2165.415 -29.6993) 
(list 2165.415 -29.8763) 
(list 2239.4375 -29.1263)))
(apply 'command (append '("pline") coords '("c")))
(setq currobj (ssadd (entlast) currobj))
(command "_layer" "set" "nitride" "")
(command "_layer" "set" "text" "")
(command "_circle" "2239.0625,-40.2693" "0.075")
(command "_circle" "2239.0625,-39.9693" "0.075")
(command "_circle" "2239.0625,-39.6693" "0.075")
(command "_circle" "2239.0625,-39.3693" "0.075")
(command "_circle" "2239.0625,-39.0693" "0.075")
(command "_circle" "2238.7625,-40.2693" "0.075")
(command "_circle" "2238.7625,-39.9693" "0.075")
(command "_circle" "2238.7625,-39.6693" "0.075")
(command "_circle" "2238.7625,-39.3693" "0.075")
(command "_circle" "2238.7625,-39.0693" "0.075")
(command "_circle" "2238.4625,-40.2693" "0.075")
(command "_circle" "2238.4625,-39.9693" "0.075")
(command "_circle" "2238.4625,-39.6693" "0.075")
(command "_circle" "2238.4625,-39.3693" "0.075")
(command "_circle" "2238.4625,-39.0693" "0.075")
(command "_circle" "2238.1625,-40.2693" "0.075")
(command "_circle" "2238.1625,-39.9693" "0.075")
(command "_circle" "2238.1625,-39.6693" "0.075")
(command "_circle" "2238.1625,-39.3693" "0.075")
(command "_circle" "2238.1625,-39.0693" "0.075")
(command "_circle" "2237.8625,-40.2693" "0.075")
(command "_circle" "2237.8625,-39.9693" "0.075")
(command "_circle" "2237.8625,-39.6693" "0.075")
(command "_circle" "2237.8625,-39.3693" "0.075")
(command "_circle" "2237.8625,-39.0693" "0.075")
(command "_layer" "set" "nitride" "")
(setq coords (list 
(list 2240.2625 -14.8263) 
(list 2240.2625 100.8184) 
(list 2239.7375 100.8184) 
(list 2239.7375 -14.8263)))
(apply 'command (append '("pline") coords '("c")))
(setq currobj (ssadd (entlast) currobj))
(command "_layer" "set" "prebias" "")
(command "_rectangle" "2239.7375,-14.8263" "2240.2625,100.8184")
(setq currobj (ssadd (entlast) currobj))
(command "_layer" "set" "nitride" "")
(setq coords (list 
(list 2240.2625 100.8184) 
(list 2240.5625 110.8184) 
(list 2240.5625 110.8184) 
(list 2240.5625 111.8184) 
(list 2314.585 111.0684) 
(list 2314.585 116.0114) 
(list 2240.5625 115.2614) 
(list 2240.5625 116.2614) 
(list 2240.5625 116.2614) 
(list 2240.2625 126.2614) 
(list 2239.7375 126.2614) 
(list 2239.4375 116.2614) 
(list 2239.4375 116.2614) 
(list 2239.4375 115.2614) 
(list 2165.415 116.0114) 
(list 2165.415 111.0684) 
(list 2239.4375 111.8184) 
(list 2239.4375 110.8184) 
(list 2239.4375 110.8184) 
(list 2239.7375 100.8184)))
(apply 'command (append '("pline") coords '("c")))
(setq currobj (ssadd (entlast) currobj))
(command "_layer" "set" "prebias" "")
(setq coords (list 
(list 2239.4375 100.8184) 
(list 2239.4375 111.8184) 
(list 2165.415 111.0684) 
(list 2165.415 116.0114) 
(list 2239.4375 115.2614) 
(list 2239.4375 126.2614) 
(list 2240.5625 126.2614) 
(list 2240.5625 115.2614) 
(list 2314.585 116.0114) 
(list 2314.585 111.0684) 
(list 2240.5625 111.8184) 
(list 2240.5625 100.8184)))
(apply 'command (append '("pline") coords '("c")))
(setq currobj (ssadd (entlast) currobj))
(command "_layer" "set" "nitride" "")
(command "_layer" "set" "fda1" "")
(setq coords (list 
(list 2240.5625 111.9614) 
(list 2314.585 111.2114) 
(list 2314.585 111.3884) 
(list 2240.5625 112.0384)))
(apply 'command (append '("pline") coords '("c")))
(setq currobj (ssadd (entlast) currobj))
(setq coords (list 
(list 2240.5625 112.1814) 
(list 2314.585 111.5314) 
(list 2314.585 111.7084) 
(list 2240.5625 112.2584)))
(apply 'command (append '("pline") coords '("c")))
(setq currobj (ssadd (entlast) currobj))
(setq coords (list 
(list 2240.5625 112.4014) 
(list 2314.585 111.8514) 
(list 2314.585 112.0284) 
(list 2240.5625 112.4784)))
(apply 'command (append '("pline") coords '("c")))
(setq currobj (ssadd (entlast) currobj))
(setq coords (list 
(list 2240.5625 112.6214) 
(list 2314.585 112.1714) 
(list 2314.585 112.3484) 
(list 2240.5625 112.6984)))
(apply 'command (append '("pline") coords '("c")))
(setq currobj (ssadd (entlast) currobj))
(setq coords (list 
(list 2240.5625 112.8414) 
(list 2314.585 112.4914) 
(list 2314.585 112.6684) 
(list 2240.5625 112.9184)))
(apply 'command (append '("pline") coords '("c")))
(setq currobj (ssadd (entlast) currobj))
(setq coords (list 
(list 2240.5625 113.0614) 
(list 2314.585 112.8114) 
(list 2314.585 112.9884) 
(list 2240.5625 113.1384)))
(apply 'command (append '("pline") coords '("c")))
(setq currobj (ssadd (entlast) currobj))
(setq coords (list 
(list 2240.5625 113.2814) 
(list 2314.585 113.1314) 
(list 2314.585 113.3084) 
(list 2240.5625 113.3584)))
(apply 'command (append '("pline") coords '("c")))
(setq currobj (ssadd (entlast) currobj))
(setq coords (list 
(list 2240.5625 113.5014) 
(list 2314.585 113.4514) 
(list 2314.585 113.6284) 
(list 2240.5625 113.5784)))
(apply 'command (append '("pline") coords '("c")))
(setq currobj (ssadd (entlast) currobj))
(setq coords (list 
(list 2240.5625 113.7214) 
(list 2314.585 113.7714) 
(list 2314.585 113.9484) 
(list 2240.5625 113.7984)))
(apply 'command (append '("pline") coords '("c")))
(setq currobj (ssadd (entlast) currobj))
(setq coords (list 
(list 2240.5625 113.9414) 
(list 2314.585 114.0914) 
(list 2314.585 114.2684) 
(list 2240.5625 114.0184)))
(apply 'command (append '("pline") coords '("c")))
(setq currobj (ssadd (entlast) currobj))
(setq coords (list 
(list 2240.5625 114.1614) 
(list 2314.585 114.4114) 
(list 2314.585 114.5884) 
(list 2240.5625 114.2384)))
(apply 'command (append '("pline") coords '("c")))
(setq currobj (ssadd (entlast) currobj))
(setq coords (list 
(list 2240.5625 114.3814) 
(list 2314.585 114.7314) 
(list 2314.585 114.9084) 
(list 2240.5625 114.4584)))
(apply 'command (append '("pline") coords '("c")))
(setq currobj (ssadd (entlast) currobj))
(setq coords (list 
(list 2240.5625 114.6014) 
(list 2314.585 115.0514) 
(list 2314.585 115.2284) 
(list 2240.5625 114.6784)))
(apply 'command (append '("pline") coords '("c")))
(setq currobj (ssadd (entlast) currobj))
(setq coords (list 
(list 2240.5625 114.8214) 
(list 2314.585 115.3714) 
(list 2314.585 115.5484) 
(list 2240.5625 114.8984)))
(apply 'command (append '("pline") coords '("c")))
(setq currobj (ssadd (entlast) currobj))
(setq coords (list 
(list 2240.5625 115.0414) 
(list 2314.585 115.6914) 
(list 2314.585 115.8684) 
(list 2240.5625 115.1184)))
(apply 'command (append '("pline") coords '("c")))
(setq currobj (ssadd (entlast) currobj))
(setq coords (list 
(list 2239.4375 115.1184) 
(list 2165.415 115.8684) 
(list 2165.415 115.6914) 
(list 2239.4375 115.0414)))
(apply 'command (append '("pline") coords '("c")))
(setq currobj (ssadd (entlast) currobj))
(setq coords (list 
(list 2239.4375 114.8984) 
(list 2165.415 115.5484) 
(list 2165.415 115.3714) 
(list 2239.4375 114.8214)))
(apply 'command (append '("pline") coords '("c")))
(setq currobj (ssadd (entlast) currobj))
(setq coords (list 
(list 2239.4375 114.6784) 
(list 2165.415 115.2284) 
(list 2165.415 115.0514) 
(list 2239.4375 114.6014)))
(apply 'command (append '("pline") coords '("c")))
(setq currobj (ssadd (entlast) currobj))
(setq coords (list 
(list 2239.4375 114.4584) 
(list 2165.415 114.9084) 
(list 2165.415 114.7314) 
(list 2239.4375 114.3814)))
(apply 'command (append '("pline") coords '("c")))
(setq currobj (ssadd (entlast) currobj))
(setq coords (list 
(list 2239.4375 114.2384) 
(list 2165.415 114.5884) 
(list 2165.415 114.4114) 
(list 2239.4375 114.1614)))
(apply 'command (append '("pline") coords '("c")))
(setq currobj (ssadd (entlast) currobj))
(setq coords (list 
(list 2239.4375 114.0184) 
(list 2165.415 114.2684) 
(list 2165.415 114.0914) 
(list 2239.4375 113.9414)))
(apply 'command (append '("pline") coords '("c")))
(setq currobj (ssadd (entlast) currobj))
(setq coords (list 
(list 2239.4375 113.7984) 
(list 2165.415 113.9484) 
(list 2165.415 113.7714) 
(list 2239.4375 113.7214)))
(apply 'command (append '("pline") coords '("c")))
(setq currobj (ssadd (entlast) currobj))
(setq coords (list 
(list 2239.4375 113.5784) 
(list 2165.415 113.6284) 
(list 2165.415 113.4514) 
(list 2239.4375 113.5014)))
(apply 'command (append '("pline") coords '("c")))
(setq currobj (ssadd (entlast) currobj))
(setq coords (list 
(list 2239.4375 113.3584) 
(list 2165.415 113.3084) 
(list 2165.415 113.1314) 
(list 2239.4375 113.2814)))
(apply 'command (append '("pline") coords '("c")))
(setq currobj (ssadd (entlast) currobj))
(setq coords (list 
(list 2239.4375 113.1384) 
(list 2165.415 112.9884) 
(list 2165.415 112.8114) 
(list 2239.4375 113.0614)))
(apply 'command (append '("pline") coords '("c")))
(setq currobj (ssadd (entlast) currobj))
(setq coords (list 
(list 2239.4375 112.9184) 
(list 2165.415 112.6684) 
(list 2165.415 112.4914) 
(list 2239.4375 112.8414)))
(apply 'command (append '("pline") coords '("c")))
(setq currobj (ssadd (entlast) currobj))
(setq coords (list 
(list 2239.4375 112.6984) 
(list 2165.415 112.3484) 
(list 2165.415 112.1714) 
(list 2239.4375 112.6214)))
(apply 'command (append '("pline") coords '("c")))
(setq currobj (ssadd (entlast) currobj))
(setq coords (list 
(list 2239.4375 112.4784) 
(list 2165.415 112.0284) 
(list 2165.415 111.8514) 
(list 2239.4375 112.4014)))
(apply 'command (append '("pline") coords '("c")))
(setq currobj (ssadd (entlast) currobj))
(setq coords (list 
(list 2239.4375 112.2584) 
(list 2165.415 111.7084) 
(list 2165.415 111.5314) 
(list 2239.4375 112.1814)))
(apply 'command (append '("pline") coords '("c")))
(setq currobj (ssadd (entlast) currobj))
(setq coords (list 
(list 2239.4375 112.0384) 
(list 2165.415 111.3884) 
(list 2165.415 111.2114) 
(list 2239.4375 111.9614)))
(apply 'command (append '("pline") coords '("c")))
(setq currobj (ssadd (entlast) currobj))
(command "_layer" "set" "nitride" "")
(command "_layer" "set" "text" "")
(command "_circle" "2239.0625,100.8184" "0.075")
(command "_circle" "2239.0625,101.1184" "0.075")
(command "_circle" "2239.0625,101.4184" "0.075")
(command "_circle" "2239.0625,101.7184" "0.075")
(command "_circle" "2239.0625,102.0184" "0.075")
(command "_circle" "2238.7625,100.8184" "0.075")
(command "_circle" "2238.7625,101.1184" "0.075")
(command "_circle" "2238.7625,101.4184" "0.075")
(command "_circle" "2238.7625,101.7184" "0.075")
(command "_circle" "2238.7625,102.0184" "0.075")
(command "_circle" "2238.4625,100.8184" "0.075")
(command "_circle" "2238.4625,101.1184" "0.075")
(command "_circle" "2238.4625,101.4184" "0.075")
(command "_circle" "2238.4625,101.7184" "0.075")
(command "_circle" "2238.4625,102.0184" "0.075")
(command "_circle" "2238.1625,100.8184" "0.075")
(command "_circle" "2238.1625,101.1184" "0.075")
(command "_circle" "2238.1625,101.4184" "0.075")
(command "_circle" "2238.1625,101.7184" "0.075")
(command "_circle" "2238.1625,102.0184" "0.075")
(command "_circle" "2237.8625,100.8184" "0.075")
(command "_circle" "2237.8625,101.1184" "0.075")
(command "_circle" "2237.8625,101.4184" "0.075")
(command "_circle" "2237.8625,101.7184" "0.075")
(command "_circle" "2237.8625,102.0184" "0.075")
(command "_layer" "set" "nitride" "")
(setq coords (list 
(list 2240.2625 126.2614) 
(list 2240.2625 241.9061) 
(list 2239.7375 241.9061) 
(list 2239.7375 126.2614)))
(apply 'command (append '("pline") coords '("c")))
(setq currobj (ssadd (entlast) currobj))
(command "_layer" "set" "prebias" "")
(command "_rectangle" "2239.7375,126.2614" "2240.2625,241.9061")
(setq currobj (ssadd (entlast) currobj))
(command "_layer" "set" "nitride" "")
(setq coords (list 
(list 2240.2625 241.9061) 
(list 2240.5625 251.9061) 
(list 2240.5625 251.9061) 
(list 2240.5625 252.9061) 
(list 2314.585 252.1561) 
(list 2314.585 257.0991) 
(list 2240.5625 256.3491) 
(list 2240.5625 257.3491) 
(list 2240.5625 257.3491) 
(list 2240.2625 267.3491) 
(list 2239.7375 267.3491) 
(list 2239.4375 257.3491) 
(list 2239.4375 257.3491) 
(list 2239.4375 256.3491) 
(list 2165.415 257.0991) 
(list 2165.415 252.1561) 
(list 2239.4375 252.9061) 
(list 2239.4375 251.9061) 
(list 2239.4375 251.9061) 
(list 2239.7375 241.9061)))
(apply 'command (append '("pline") coords '("c")))
(setq currobj (ssadd (entlast) currobj))
(command "_layer" "set" "prebias" "")
(setq coords (list 
(list 2239.4375 241.9061) 
(list 2239.4375 252.9061) 
(list 2165.415 252.1561) 
(list 2165.415 257.0991) 
(list 2239.4375 256.3491) 
(list 2239.4375 267.3491) 
(list 2240.5625 267.3491) 
(list 2240.5625 256.3491) 
(list 2314.585 257.0991) 
(list 2314.585 252.1561) 
(list 2240.5625 252.9061) 
(list 2240.5625 241.9061)))
(apply 'command (append '("pline") coords '("c")))
(setq currobj (ssadd (entlast) currobj))
(command "_layer" "set" "nitride" "")
(command "_layer" "set" "fda1" "")
(setq coords (list 
(list 2240.5625 253.0491) 
(list 2314.585 252.2991) 
(list 2314.585 252.4761) 
(list 2240.5625 253.1261)))
(apply 'command (append '("pline") coords '("c")))
(setq currobj (ssadd (entlast) currobj))
(setq coords (list 
(list 2240.5625 253.2691) 
(list 2314.585 252.6191) 
(list 2314.585 252.7961) 
(list 2240.5625 253.3461)))
(apply 'command (append '("pline") coords '("c")))
(setq currobj (ssadd (entlast) currobj))
(setq coords (list 
(list 2240.5625 253.4891) 
(list 2314.585 252.9391) 
(list 2314.585 253.1161) 
(list 2240.5625 253.5661)))
(apply 'command (append '("pline") coords '("c")))
(setq currobj (ssadd (entlast) currobj))
(setq coords (list 
(list 2240.5625 253.7091) 
(list 2314.585 253.2591) 
(list 2314.585 253.4361) 
(list 2240.5625 253.7861)))
(apply 'command (append '("pline") coords '("c")))
(setq currobj (ssadd (entlast) currobj))
(setq coords (list 
(list 2240.5625 253.9291) 
(list 2314.585 253.5791) 
(list 2314.585 253.7561) 
(list 2240.5625 254.0061)))
(apply 'command (append '("pline") coords '("c")))
(setq currobj (ssadd (entlast) currobj))
(setq coords (list 
(list 2240.5625 254.1491) 
(list 2314.585 253.8991) 
(list 2314.585 254.0761) 
(list 2240.5625 254.2261)))
(apply 'command (append '("pline") coords '("c")))
(setq currobj (ssadd (entlast) currobj))
(setq coords (list 
(list 2240.5625 254.3691) 
(list 2314.585 254.2191) 
(list 2314.585 254.3961) 
(list 2240.5625 254.4461)))
(apply 'command (append '("pline") coords '("c")))
(setq currobj (ssadd (entlast) currobj))
(setq coords (list 
(list 2240.5625 254.5891) 
(list 2314.585 254.5391) 
(list 2314.585 254.7161) 
(list 2240.5625 254.6661)))
(apply 'command (append '("pline") coords '("c")))
(setq currobj (ssadd (entlast) currobj))
(setq coords (list 
(list 2240.5625 254.8091) 
(list 2314.585 254.8591) 
(list 2314.585 255.0361) 
(list 2240.5625 254.8861)))
(apply 'command (append '("pline") coords '("c")))
(setq currobj (ssadd (entlast) currobj))
(setq coords (list 
(list 2240.5625 255.0291) 
(list 2314.585 255.1791) 
(list 2314.585 255.3561) 
(list 2240.5625 255.1061)))
(apply 'command (append '("pline") coords '("c")))
(setq currobj (ssadd (entlast) currobj))
(setq coords (list 
(list 2240.5625 255.2491) 
(list 2314.585 255.4991) 
(list 2314.585 255.6761) 
(list 2240.5625 255.3261)))
(apply 'command (append '("pline") coords '("c")))
(setq currobj (ssadd (entlast) currobj))
(setq coords (list 
(list 2240.5625 255.4691) 
(list 2314.585 255.8191) 
(list 2314.585 255.9961) 
(list 2240.5625 255.5461)))
(apply 'command (append '("pline") coords '("c")))
(setq currobj (ssadd (entlast) currobj))
(setq coords (list 
(list 2240.5625 255.6891) 
(list 2314.585 256.1391) 
(list 2314.585 256.3161) 
(list 2240.5625 255.7661)))
(apply 'command (append '("pline") coords '("c")))
(setq currobj (ssadd (entlast) currobj))
(setq coords (list 
(list 2240.5625 255.9091) 
(list 2314.585 256.4591) 
(list 2314.585 256.6361) 
(list 2240.5625 255.9861)))
(apply 'command (append '("pline") coords '("c")))
(setq currobj (ssadd (entlast) currobj))
(setq coords (list 
(list 2240.5625 256.1291) 
(list 2314.585 256.7791) 
(list 2314.585 256.9561) 
(list 2240.5625 256.2061)))
(apply 'command (append '("pline") coords '("c")))
(setq currobj (ssadd (entlast) currobj))
(setq coords (list 
(list 2239.4375 256.2061) 
(list 2165.415 256.9561) 
(list 2165.415 256.7791) 
(list 2239.4375 256.1291)))
(apply 'command (append '("pline") coords '("c")))
(setq currobj (ssadd (entlast) currobj))
(setq coords (list 
(list 2239.4375 255.9861) 
(list 2165.415 256.6361) 
(list 2165.415 256.4591) 
(list 2239.4375 255.9091)))
(apply 'command (append '("pline") coords '("c")))
(setq currobj (ssadd (entlast) currobj))
(setq coords (list 
(list 2239.4375 255.7661) 
(list 2165.415 256.3161) 
(list 2165.415 256.1391) 
(list 2239.4375 255.6891)))
(apply 'command (append '("pline") coords '("c")))
(setq currobj (ssadd (entlast) currobj))
(setq coords (list 
(list 2239.4375 255.5461) 
(list 2165.415 255.9961) 
(list 2165.415 255.8191) 
(list 2239.4375 255.4691)))
(apply 'command (append '("pline") coords '("c")))
(setq currobj (ssadd (entlast) currobj))
(setq coords (list 
(list 2239.4375 255.3261) 
(list 2165.415 255.6761) 
(list 2165.415 255.4991) 
(list 2239.4375 255.2491)))
(apply 'command (append '("pline") coords '("c")))
(setq currobj (ssadd (entlast) currobj))
(setq coords (list 
(list 2239.4375 255.1061) 
(list 2165.415 255.3561) 
(list 2165.415 255.1791) 
(list 2239.4375 255.0291)))
(apply 'command (append '("pline") coords '("c")))
(setq currobj (ssadd (entlast) currobj))
(setq coords (list 
(list 2239.4375 254.8861) 
(list 2165.415 255.0361) 
(list 2165.415 254.8591) 
(list 2239.4375 254.8091)))
(apply 'command (append '("pline") coords '("c")))
(setq currobj (ssadd (entlast) currobj))
(setq coords (list 
(list 2239.4375 254.6661) 
(list 2165.415 254.7161) 
(list 2165.415 254.5391) 
(list 2239.4375 254.5891)))
(apply 'command (append '("pline") coords '("c")))
(setq currobj (ssadd (entlast) currobj))
(setq coords (list 
(list 2239.4375 254.4461) 
(list 2165.415 254.3961) 
(list 2165.415 254.2191) 
(list 2239.4375 254.3691)))
(apply 'command (append '("pline") coords '("c")))
(setq currobj (ssadd (entlast) currobj))
(setq coords (list 
(list 2239.4375 254.2261) 
(list 2165.415 254.0761) 
(list 2165.415 253.8991) 
(list 2239.4375 254.1491)))
(apply 'command (append '("pline") coords '("c")))
(setq currobj (ssadd (entlast) currobj))
(setq coords (list 
(list 2239.4375 254.0061) 
(list 2165.415 253.7561) 
(list 2165.415 253.5791) 
(list 2239.4375 253.9291)))
(apply 'command (append '("pline") coords '("c")))
(setq currobj (ssadd (entlast) currobj))
(setq coords (list 
(list 2239.4375 253.7861) 
(list 2165.415 253.4361) 
(list 2165.415 253.2591) 
(list 2239.4375 253.7091)))
(apply 'command (append '("pline") coords '("c")))
(setq currobj (ssadd (entlast) currobj))
(setq coords (list 
(list 2239.4375 253.5661) 
(list 2165.415 253.1161) 
(list 2165.415 252.9391) 
(list 2239.4375 253.4891)))
(apply 'command (append '("pline") coords '("c")))
(setq currobj (ssadd (entlast) currobj))
(setq coords (list 
(list 2239.4375 253.3461) 
(list 2165.415 252.7961) 
(list 2165.415 252.6191) 
(list 2239.4375 253.2691)))
(apply 'command (append '("pline") coords '("c")))
(setq currobj (ssadd (entlast) currobj))
(setq coords (list 
(list 2239.4375 253.1261) 
(list 2165.415 252.4761) 
(list 2165.415 252.2991) 
(list 2239.4375 253.0491)))
(apply 'command (append '("pline") coords '("c")))
(setq currobj (ssadd (entlast) currobj))
(command "_layer" "set" "nitride" "")
(command "_layer" "set" "text" "")
(command "_circle" "2239.0625,241.9061" "0.075")
(command "_circle" "2239.0625,242.2061" "0.075")
(command "_circle" "2239.0625,242.5061" "0.075")
(command "_circle" "2239.0625,242.8061" "0.075")
(command "_circle" "2239.0625,243.1061" "0.075")
(command "_circle" "2238.7625,241.9061" "0.075")
(command "_circle" "2238.7625,242.2061" "0.075")
(command "_circle" "2238.7625,242.5061" "0.075")
(command "_circle" "2238.7625,242.8061" "0.075")
(command "_circle" "2238.7625,243.1061" "0.075")
(command "_circle" "2238.4625,241.9061" "0.075")
(command "_circle" "2238.4625,242.2061" "0.075")
(command "_circle" "2238.4625,242.5061" "0.075")
(command "_circle" "2238.4625,242.8061" "0.075")
(command "_circle" "2238.4625,243.1061" "0.075")
(command "_circle" "2238.1625,241.9061" "0.075")
(command "_circle" "2238.1625,242.2061" "0.075")
(command "_circle" "2238.1625,242.5061" "0.075")
(command "_circle" "2238.1625,242.8061" "0.075")
(command "_circle" "2238.1625,243.1061" "0.075")
(command "_circle" "2237.8625,241.9061" "0.075")
(command "_circle" "2237.8625,242.2061" "0.075")
(command "_circle" "2237.8625,242.5061" "0.075")
(command "_circle" "2237.8625,242.8061" "0.075")
(command "_circle" "2237.8625,243.1061" "0.075")
(command "_layer" "set" "nitride" "")
(setq coords (list 
(list 2240.2625 267.3491) 
(list 2240.2625 382.9939) 
(list 2239.7375 382.9939) 
(list 2239.7375 267.3491)))
(apply 'command (append '("pline") coords '("c")))
(setq currobj (ssadd (entlast) currobj))
(command "_layer" "set" "prebias" "")
(command "_rectangle" "2239.7375,267.3491" "2240.2625,382.9939")
(setq currobj (ssadd (entlast) currobj))
(command "_layer" "set" "nitride" "")
(setq coords (list 
(list 2240.2625 382.9939) 
(list 2240.5625 392.9939) 
(list 2240.5625 392.9939) 
(list 2240.5625 393.9939) 
(list 2314.585 393.2439) 
(list 2314.585 398.1869) 
(list 2240.5625 397.4369) 
(list 2240.5625 398.4369) 
(list 2240.5625 398.4369) 
(list 2240.2625 408.4369) 
(list 2239.7375 408.4369) 
(list 2239.4375 398.4369) 
(list 2239.4375 398.4369) 
(list 2239.4375 397.4369) 
(list 2165.415 398.1869) 
(list 2165.415 393.2439) 
(list 2239.4375 393.9939) 
(list 2239.4375 392.9939) 
(list 2239.4375 392.9939) 
(list 2239.7375 382.9939)))
(apply 'command (append '("pline") coords '("c")))
(setq currobj (ssadd (entlast) currobj))
(command "_layer" "set" "prebias" "")
(setq coords (list 
(list 2239.4375 382.9939) 
(list 2239.4375 393.9939) 
(list 2165.415 393.2439) 
(list 2165.415 398.1869) 
(list 2239.4375 397.4369) 
(list 2239.4375 408.4369) 
(list 2240.5625 408.4369) 
(list 2240.5625 397.4369) 
(list 2314.585 398.1869) 
(list 2314.585 393.2439) 
(list 2240.5625 393.9939) 
(list 2240.5625 382.9939)))
(apply 'command (append '("pline") coords '("c")))
(setq currobj (ssadd (entlast) currobj))
(command "_layer" "set" "nitride" "")
(command "_layer" "set" "fda1" "")
(setq coords (list 
(list 2240.5625 394.1369) 
(list 2314.585 393.3869) 
(list 2314.585 393.5639) 
(list 2240.5625 394.2139)))
(apply 'command (append '("pline") coords '("c")))
(setq currobj (ssadd (entlast) currobj))
(setq coords (list 
(list 2240.5625 394.3569) 
(list 2314.585 393.7069) 
(list 2314.585 393.8839) 
(list 2240.5625 394.4339)))
(apply 'command (append '("pline") coords '("c")))
(setq currobj (ssadd (entlast) currobj))
(setq coords (list 
(list 2240.5625 394.5769) 
(list 2314.585 394.0269) 
(list 2314.585 394.2039) 
(list 2240.5625 394.6539)))
(apply 'command (append '("pline") coords '("c")))
(setq currobj (ssadd (entlast) currobj))
(setq coords (list 
(list 2240.5625 394.7969) 
(list 2314.585 394.3469) 
(list 2314.585 394.5239) 
(list 2240.5625 394.8739)))
(apply 'command (append '("pline") coords '("c")))
(setq currobj (ssadd (entlast) currobj))
(setq coords (list 
(list 2240.5625 395.0169) 
(list 2314.585 394.6669) 
(list 2314.585 394.8439) 
(list 2240.5625 395.0939)))
(apply 'command (append '("pline") coords '("c")))
(setq currobj (ssadd (entlast) currobj))
(setq coords (list 
(list 2240.5625 395.2369) 
(list 2314.585 394.9869) 
(list 2314.585 395.1639) 
(list 2240.5625 395.3139)))
(apply 'command (append '("pline") coords '("c")))
(setq currobj (ssadd (entlast) currobj))
(setq coords (list 
(list 2240.5625 395.4569) 
(list 2314.585 395.3069) 
(list 2314.585 395.4839) 
(list 2240.5625 395.5339)))
(apply 'command (append '("pline") coords '("c")))
(setq currobj (ssadd (entlast) currobj))
(setq coords (list 
(list 2240.5625 395.6769) 
(list 2314.585 395.6269) 
(list 2314.585 395.8039) 
(list 2240.5625 395.7539)))
(apply 'command (append '("pline") coords '("c")))
(setq currobj (ssadd (entlast) currobj))
(setq coords (list 
(list 2240.5625 395.8969) 
(list 2314.585 395.9469) 
(list 2314.585 396.1239) 
(list 2240.5625 395.9739)))
(apply 'command (append '("pline") coords '("c")))
(setq currobj (ssadd (entlast) currobj))
(setq coords (list 
(list 2240.5625 396.1169) 
(list 2314.585 396.2669) 
(list 2314.585 396.4439) 
(list 2240.5625 396.1939)))
(apply 'command (append '("pline") coords '("c")))
(setq currobj (ssadd (entlast) currobj))
(setq coords (list 
(list 2240.5625 396.3369) 
(list 2314.585 396.5869) 
(list 2314.585 396.7639) 
(list 2240.5625 396.4139)))
(apply 'command (append '("pline") coords '("c")))
(setq currobj (ssadd (entlast) currobj))
(setq coords (list 
(list 2240.5625 396.5569) 
(list 2314.585 396.9069) 
(list 2314.585 397.0839) 
(list 2240.5625 396.6339)))
(apply 'command (append '("pline") coords '("c")))
(setq currobj (ssadd (entlast) currobj))
(setq coords (list 
(list 2240.5625 396.7769) 
(list 2314.585 397.2269) 
(list 2314.585 397.4039) 
(list 2240.5625 396.8539)))
(apply 'command (append '("pline") coords '("c")))
(setq currobj (ssadd (entlast) currobj))
(setq coords (list 
(list 2240.5625 396.9969) 
(list 2314.585 397.5469) 
(list 2314.585 397.7239) 
(list 2240.5625 397.0739)))
(apply 'command (append '("pline") coords '("c")))
(setq currobj (ssadd (entlast) currobj))
(setq coords (list 
(list 2240.5625 397.2169) 
(list 2314.585 397.8669) 
(list 2314.585 398.0439) 
(list 2240.5625 397.2939)))
(apply 'command (append '("pline") coords '("c")))
(setq currobj (ssadd (entlast) currobj))
(setq coords (list 
(list 2239.4375 397.2939) 
(list 2165.415 398.0439) 
(list 2165.415 397.8669) 
(list 2239.4375 397.2169)))
(apply 'command (append '("pline") coords '("c")))
(setq currobj (ssadd (entlast) currobj))
(setq coords (list 
(list 2239.4375 397.0739) 
(list 2165.415 397.7239) 
(list 2165.415 397.5469) 
(list 2239.4375 396.9969)))
(apply 'command (append '("pline") coords '("c")))
(setq currobj (ssadd (entlast) currobj))
(setq coords (list 
(list 2239.4375 396.8539) 
(list 2165.415 397.4039) 
(list 2165.415 397.2269) 
(list 2239.4375 396.7769)))
(apply 'command (append '("pline") coords '("c")))
(setq currobj (ssadd (entlast) currobj))
(setq coords (list 
(list 2239.4375 396.6339) 
(list 2165.415 397.0839) 
(list 2165.415 396.9069) 
(list 2239.4375 396.5569)))
(apply 'command (append '("pline") coords '("c")))
(setq currobj (ssadd (entlast) currobj))
(setq coords (list 
(list 2239.4375 396.4139) 
(list 2165.415 396.7639) 
(list 2165.415 396.5869) 
(list 2239.4375 396.3369)))
(apply 'command (append '("pline") coords '("c")))
(setq currobj (ssadd (entlast) currobj))
(setq coords (list 
(list 2239.4375 396.1939) 
(list 2165.415 396.4439) 
(list 2165.415 396.2669) 
(list 2239.4375 396.1169)))
(apply 'command (append '("pline") coords '("c")))
(setq currobj (ssadd (entlast) currobj))
(setq coords (list 
(list 2239.4375 395.9739) 
(list 2165.415 396.1239) 
(list 2165.415 395.9469) 
(list 2239.4375 395.8969)))
(apply 'command (append '("pline") coords '("c")))
(setq currobj (ssadd (entlast) currobj))
(setq coords (list 
(list 2239.4375 395.7539) 
(list 2165.415 395.8039) 
(list 2165.415 395.6269) 
(list 2239.4375 395.6769)))
(apply 'command (append '("pline") coords '("c")))
(setq currobj (ssadd (entlast) currobj))
(setq coords (list 
(list 2239.4375 395.5339) 
(list 2165.415 395.4839) 
(list 2165.415 395.3069) 
(list 2239.4375 395.4569)))
(apply 'command (append '("pline") coords '("c")))
(setq currobj (ssadd (entlast) currobj))
(setq coords (list 
(list 2239.4375 395.3139) 
(list 2165.415 395.1639) 
(list 2165.415 394.9869) 
(list 2239.4375 395.2369)))
(apply 'command (append '("pline") coords '("c")))
(setq currobj (ssadd (entlast) currobj))
(setq coords (list 
(list 2239.4375 395.0939) 
(list 2165.415 394.8439) 
(list 2165.415 394.6669) 
(list 2239.4375 395.0169)))
(apply 'command (append '("pline") coords '("c")))
(setq currobj (ssadd (entlast) currobj))
(setq coords (list 
(list 2239.4375 394.8739) 
(list 2165.415 394.5239) 
(list 2165.415 394.3469) 
(list 2239.4375 394.7969)))
(apply 'command (append '("pline") coords '("c")))
(setq currobj (ssadd (entlast) currobj))
(setq coords (list 
(list 2239.4375 394.6539) 
(list 2165.415 394.2039) 
(list 2165.415 394.0269) 
(list 2239.4375 394.5769)))
(apply 'command (append '("pline") coords '("c")))
(setq currobj (ssadd (entlast) currobj))
(setq coords (list 
(list 2239.4375 394.4339) 
(list 2165.415 393.8839) 
(list 2165.415 393.7069) 
(list 2239.4375 394.3569)))
(apply 'command (append '("pline") coords '("c")))
(setq currobj (ssadd (entlast) currobj))
(setq coords (list 
(list 2239.4375 394.2139) 
(list 2165.415 393.5639) 
(list 2165.415 393.3869) 
(list 2239.4375 394.1369)))
(apply 'command (append '("pline") coords '("c")))
(setq currobj (ssadd (entlast) currobj))
(command "_layer" "set" "nitride" "")
(command "_layer" "set" "text" "")
(command "_circle" "2239.0625,382.9939" "0.075")
(command "_circle" "2239.0625,383.2939" "0.075")
(command "_circle" "2239.0625,383.5939" "0.075")
(command "_circle" "2239.0625,383.8939" "0.075")
(command "_circle" "2239.0625,384.1939" "0.075")
(command "_circle" "2238.7625,382.9939" "0.075")
(command "_circle" "2238.7625,383.2939" "0.075")
(command "_circle" "2238.7625,383.5939" "0.075")
(command "_circle" "2238.7625,383.8939" "0.075")
(command "_circle" "2238.7625,384.1939" "0.075")
(command "_circle" "2238.4625,382.9939" "0.075")
(command "_circle" "2238.4625,383.2939" "0.075")
(command "_circle" "2238.4625,383.5939" "0.075")
(command "_circle" "2238.4625,383.8939" "0.075")
(command "_circle" "2238.4625,384.1939" "0.075")
(command "_circle" "2238.1625,382.9939" "0.075")
(command "_circle" "2238.1625,383.2939" "0.075")
(command "_circle" "2238.1625,383.5939" "0.075")
(command "_circle" "2238.1625,383.8939" "0.075")
(command "_circle" "2238.1625,384.1939" "0.075")
(command "_circle" "2237.8625,382.9939" "0.075")
(command "_circle" "2237.8625,383.2939" "0.075")
(command "_circle" "2237.8625,383.5939" "0.075")
(command "_circle" "2237.8625,383.8939" "0.075")
(command "_circle" "2237.8625,384.1939" "0.075")
(command "_layer" "set" "nitride" "")
(setq coords (list 
(list 2240.2625 408.4369) 
(list 2240.2625 524.0816) 
(list 2239.7375 524.0816) 
(list 2239.7375 408.4369)))
(apply 'command (append '("pline") coords '("c")))
(setq currobj (ssadd (entlast) currobj))
(command "_layer" "set" "prebias" "")
(command "_rectangle" "2239.7375,408.4369" "2240.2625,524.0816")
(setq currobj (ssadd (entlast) currobj))
(command "_layer" "set" "nitride" "")
(setq coords (list 
(list 2240.2625 524.0816) 
(list 2240.5625 534.0816) 
(list 2240.5625 534.0816) 
(list 2240.5625 535.0816) 
(list 2314.585 534.3316) 
(list 2314.585 539.2746) 
(list 2240.5625 538.5246) 
(list 2240.5625 539.5246) 
(list 2240.5625 539.5246) 
(list 2240.2625 549.5246) 
(list 2239.7375 549.5246) 
(list 2239.4375 539.5246) 
(list 2239.4375 539.5246) 
(list 2239.4375 538.5246) 
(list 2165.415 539.2746) 
(list 2165.415 534.3316) 
(list 2239.4375 535.0816) 
(list 2239.4375 534.0816) 
(list 2239.4375 534.0816) 
(list 2239.7375 524.0816)))
(apply 'command (append '("pline") coords '("c")))
(setq currobj (ssadd (entlast) currobj))
(command "_layer" "set" "prebias" "")
(setq coords (list 
(list 2239.4375 524.0816) 
(list 2239.4375 535.0816) 
(list 2165.415 534.3316) 
(list 2165.415 539.2746) 
(list 2239.4375 538.5246) 
(list 2239.4375 549.5246) 
(list 2240.5625 549.5246) 
(list 2240.5625 538.5246) 
(list 2314.585 539.2746) 
(list 2314.585 534.3316) 
(list 2240.5625 535.0816) 
(list 2240.5625 524.0816)))
(apply 'command (append '("pline") coords '("c")))
(setq currobj (ssadd (entlast) currobj))
(command "_layer" "set" "nitride" "")
(command "_layer" "set" "fda1" "")
(setq coords (list 
(list 2240.5625 535.2246) 
(list 2314.585 534.4746) 
(list 2314.585 534.6516) 
(list 2240.5625 535.3016)))
(apply 'command (append '("pline") coords '("c")))
(setq currobj (ssadd (entlast) currobj))
(setq coords (list 
(list 2240.5625 535.4446) 
(list 2314.585 534.7946) 
(list 2314.585 534.9716) 
(list 2240.5625 535.5216)))
(apply 'command (append '("pline") coords '("c")))
(setq currobj (ssadd (entlast) currobj))
(setq coords (list 
(list 2240.5625 535.6646) 
(list 2314.585 535.1146) 
(list 2314.585 535.2916) 
(list 2240.5625 535.7416)))
(apply 'command (append '("pline") coords '("c")))
(setq currobj (ssadd (entlast) currobj))
(setq coords (list 
(list 2240.5625 535.8846) 
(list 2314.585 535.4346) 
(list 2314.585 535.6116) 
(list 2240.5625 535.9616)))
(apply 'command (append '("pline") coords '("c")))
(setq currobj (ssadd (entlast) currobj))
(setq coords (list 
(list 2240.5625 536.1046) 
(list 2314.585 535.7546) 
(list 2314.585 535.9316) 
(list 2240.5625 536.1816)))
(apply 'command (append '("pline") coords '("c")))
(setq currobj (ssadd (entlast) currobj))
(setq coords (list 
(list 2240.5625 536.3246) 
(list 2314.585 536.0746) 
(list 2314.585 536.2516) 
(list 2240.5625 536.4016)))
(apply 'command (append '("pline") coords '("c")))
(setq currobj (ssadd (entlast) currobj))
(setq coords (list 
(list 2240.5625 536.5446) 
(list 2314.585 536.3946) 
(list 2314.585 536.5716) 
(list 2240.5625 536.6216)))
(apply 'command (append '("pline") coords '("c")))
(setq currobj (ssadd (entlast) currobj))
(setq coords (list 
(list 2240.5625 536.7646) 
(list 2314.585 536.7146) 
(list 2314.585 536.8916) 
(list 2240.5625 536.8416)))
(apply 'command (append '("pline") coords '("c")))
(setq currobj (ssadd (entlast) currobj))
(setq coords (list 
(list 2240.5625 536.9846) 
(list 2314.585 537.0346) 
(list 2314.585 537.2116) 
(list 2240.5625 537.0616)))
(apply 'command (append '("pline") coords '("c")))
(setq currobj (ssadd (entlast) currobj))
(setq coords (list 
(list 2240.5625 537.2046) 
(list 2314.585 537.3546) 
(list 2314.585 537.5316) 
(list 2240.5625 537.2816)))
(apply 'command (append '("pline") coords '("c")))
(setq currobj (ssadd (entlast) currobj))
(setq coords (list 
(list 2240.5625 537.4246) 
(list 2314.585 537.6746) 
(list 2314.585 537.8516) 
(list 2240.5625 537.5016)))
(apply 'command (append '("pline") coords '("c")))
(setq currobj (ssadd (entlast) currobj))
(setq coords (list 
(list 2240.5625 537.6446) 
(list 2314.585 537.9946) 
(list 2314.585 538.1716) 
(list 2240.5625 537.7216)))
(apply 'command (append '("pline") coords '("c")))
(setq currobj (ssadd (entlast) currobj))
(setq coords (list 
(list 2240.5625 537.8646) 
(list 2314.585 538.3146) 
(list 2314.585 538.4916) 
(list 2240.5625 537.9416)))
(apply 'command (append '("pline") coords '("c")))
(setq currobj (ssadd (entlast) currobj))
(setq coords (list 
(list 2240.5625 538.0846) 
(list 2314.585 538.6346) 
(list 2314.585 538.8116) 
(list 2240.5625 538.1616)))
(apply 'command (append '("pline") coords '("c")))
(setq currobj (ssadd (entlast) currobj))
(setq coords (list 
(list 2240.5625 538.3046) 
(list 2314.585 538.9546) 
(list 2314.585 539.1316) 
(list 2240.5625 538.3816)))
(apply 'command (append '("pline") coords '("c")))
(setq currobj (ssadd (entlast) currobj))
(setq coords (list 
(list 2239.4375 538.3816) 
(list 2165.415 539.1316) 
(list 2165.415 538.9546) 
(list 2239.4375 538.3046)))
(apply 'command (append '("pline") coords '("c")))
(setq currobj (ssadd (entlast) currobj))
(setq coords (list 
(list 2239.4375 538.1616) 
(list 2165.415 538.8116) 
(list 2165.415 538.6346) 
(list 2239.4375 538.0846)))
(apply 'command (append '("pline") coords '("c")))
(setq currobj (ssadd (entlast) currobj))
(setq coords (list 
(list 2239.4375 537.9416) 
(list 2165.415 538.4916) 
(list 2165.415 538.3146) 
(list 2239.4375 537.8646)))
(apply 'command (append '("pline") coords '("c")))
(setq currobj (ssadd (entlast) currobj))
(setq coords (list 
(list 2239.4375 537.7216) 
(list 2165.415 538.1716) 
(list 2165.415 537.9946) 
(list 2239.4375 537.6446)))
(apply 'command (append '("pline") coords '("c")))
(setq currobj (ssadd (entlast) currobj))
(setq coords (list 
(list 2239.4375 537.5016) 
(list 2165.415 537.8516) 
(list 2165.415 537.6746) 
(list 2239.4375 537.4246)))
(apply 'command (append '("pline") coords '("c")))
(setq currobj (ssadd (entlast) currobj))
(setq coords (list 
(list 2239.4375 537.2816) 
(list 2165.415 537.5316) 
(list 2165.415 537.3546) 
(list 2239.4375 537.2046)))
(apply 'command (append '("pline") coords '("c")))
(setq currobj (ssadd (entlast) currobj))
(setq coords (list 
(list 2239.4375 537.0616) 
(list 2165.415 537.2116) 
(list 2165.415 537.0346) 
(list 2239.4375 536.9846)))
(apply 'command (append '("pline") coords '("c")))
(setq currobj (ssadd (entlast) currobj))
(setq coords (list 
(list 2239.4375 536.8416) 
(list 2165.415 536.8916) 
(list 2165.415 536.7146) 
(list 2239.4375 536.7646)))
(apply 'command (append '("pline") coords '("c")))
(setq currobj (ssadd (entlast) currobj))
(setq coords (list 
(list 2239.4375 536.6216) 
(list 2165.415 536.5716) 
(list 2165.415 536.3946) 
(list 2239.4375 536.5446)))
(apply 'command (append '("pline") coords '("c")))
(setq currobj (ssadd (entlast) currobj))
(setq coords (list 
(list 2239.4375 536.4016) 
(list 2165.415 536.2516) 
(list 2165.415 536.0746) 
(list 2239.4375 536.3246)))
(apply 'command (append '("pline") coords '("c")))
(setq currobj (ssadd (entlast) currobj))
(setq coords (list 
(list 2239.4375 536.1816) 
(list 2165.415 535.9316) 
(list 2165.415 535.7546) 
(list 2239.4375 536.1046)))
(apply 'command (append '("pline") coords '("c")))
(setq currobj (ssadd (entlast) currobj))
(setq coords (list 
(list 2239.4375 535.9616) 
(list 2165.415 535.6116) 
(list 2165.415 535.4346) 
(list 2239.4375 535.8846)))
(apply 'command (append '("pline") coords '("c")))
(setq currobj (ssadd (entlast) currobj))
(setq coords (list 
(list 2239.4375 535.7416) 
(list 2165.415 535.2916) 
(list 2165.415 535.1146) 
(list 2239.4375 535.6646)))
(apply 'command (append '("pline") coords '("c")))
(setq currobj (ssadd (entlast) currobj))
(setq coords (list 
(list 2239.4375 535.5216) 
(list 2165.415 534.9716) 
(list 2165.415 534.7946) 
(list 2239.4375 535.4446)))
(apply 'command (append '("pline") coords '("c")))
(setq currobj (ssadd (entlast) currobj))
(setq coords (list 
(list 2239.4375 535.3016) 
(list 2165.415 534.6516) 
(list 2165.415 534.4746) 
(list 2239.4375 535.2246)))
(apply 'command (append '("pline") coords '("c")))
(setq currobj (ssadd (entlast) currobj))
(command "_layer" "set" "nitride" "")
(command "_layer" "set" "text" "")
(command "_circle" "2239.0625,524.0816" "0.075")
(command "_circle" "2239.0625,524.3816" "0.075")
(command "_circle" "2239.0625,524.6816" "0.075")
(command "_circle" "2239.0625,524.9816" "0.075")
(command "_circle" "2239.0625,525.2816" "0.075")
(command "_circle" "2238.7625,524.0816" "0.075")
(command "_circle" "2238.7625,524.3816" "0.075")
(command "_circle" "2238.7625,524.6816" "0.075")
(command "_circle" "2238.7625,524.9816" "0.075")
(command "_circle" "2238.7625,525.2816" "0.075")
(command "_circle" "2238.4625,524.0816" "0.075")
(command "_circle" "2238.4625,524.3816" "0.075")
(command "_circle" "2238.4625,524.6816" "0.075")
(command "_circle" "2238.4625,524.9816" "0.075")
(command "_circle" "2238.4625,525.2816" "0.075")
(command "_circle" "2238.1625,524.0816" "0.075")
(command "_circle" "2238.1625,524.3816" "0.075")
(command "_circle" "2238.1625,524.6816" "0.075")
(command "_circle" "2238.1625,524.9816" "0.075")
(command "_circle" "2238.1625,525.2816" "0.075")
(command "_circle" "2237.8625,524.0816" "0.075")
(command "_circle" "2237.8625,524.3816" "0.075")
(command "_circle" "2237.8625,524.6816" "0.075")
(command "_circle" "2237.8625,524.9816" "0.075")
(command "_circle" "2237.8625,525.2816" "0.075")
(command "_layer" "set" "nitride" "")
(setq coords (list 
(list 2240.2625 549.5246) 
(list 2240.2625 665.1693) 
(list 2239.7375 665.1693) 
(list 2239.7375 549.5246)))
(apply 'command (append '("pline") coords '("c")))
(setq currobj (ssadd (entlast) currobj))
(command "_layer" "set" "prebias" "")
(command "_rectangle" "2239.7375,549.5246" "2240.2625,665.1693")
(setq currobj (ssadd (entlast) currobj))
(command "_layer" "set" "nitride" "")
(setq coords (list 
(list 2240.2625 665.1693) 
(list 2240.5625 675.1693) 
(list 2240.5625 675.1693) 
(list 2240.5625 676.1693) 
(list 2314.585 675.4193) 
(list 2314.585 680.3623) 
(list 2240.5625 679.6123) 
(list 2240.5625 680.6123) 
(list 2240.5625 680.6123) 
(list 2240.2625 690.6123) 
(list 2239.7375 690.6123) 
(list 2239.4375 680.6123) 
(list 2239.4375 680.6123) 
(list 2239.4375 679.6123) 
(list 2165.415 680.3623) 
(list 2165.415 675.4193) 
(list 2239.4375 676.1693) 
(list 2239.4375 675.1693) 
(list 2239.4375 675.1693) 
(list 2239.7375 665.1693)))
(apply 'command (append '("pline") coords '("c")))
(setq currobj (ssadd (entlast) currobj))
(command "_layer" "set" "prebias" "")
(setq coords (list 
(list 2239.4375 665.1693) 
(list 2239.4375 676.1693) 
(list 2165.415 675.4193) 
(list 2165.415 680.3623) 
(list 2239.4375 679.6123) 
(list 2239.4375 690.6123) 
(list 2240.5625 690.6123) 
(list 2240.5625 679.6123) 
(list 2314.585 680.3623) 
(list 2314.585 675.4193) 
(list 2240.5625 676.1693) 
(list 2240.5625 665.1693)))
(apply 'command (append '("pline") coords '("c")))
(setq currobj (ssadd (entlast) currobj))
(command "_layer" "set" "nitride" "")
(command "_layer" "set" "fda1" "")
(setq coords (list 
(list 2240.5625 676.3123) 
(list 2314.585 675.5623) 
(list 2314.585 675.7393) 
(list 2240.5625 676.3893)))
(apply 'command (append '("pline") coords '("c")))
(setq currobj (ssadd (entlast) currobj))
(setq coords (list 
(list 2240.5625 676.5323) 
(list 2314.585 675.8823) 
(list 2314.585 676.0593) 
(list 2240.5625 676.6093)))
(apply 'command (append '("pline") coords '("c")))
(setq currobj (ssadd (entlast) currobj))
(setq coords (list 
(list 2240.5625 676.7523) 
(list 2314.585 676.2023) 
(list 2314.585 676.3793) 
(list 2240.5625 676.8293)))
(apply 'command (append '("pline") coords '("c")))
(setq currobj (ssadd (entlast) currobj))
(setq coords (list 
(list 2240.5625 676.9723) 
(list 2314.585 676.5223) 
(list 2314.585 676.6993) 
(list 2240.5625 677.0493)))
(apply 'command (append '("pline") coords '("c")))
(setq currobj (ssadd (entlast) currobj))
(setq coords (list 
(list 2240.5625 677.1923) 
(list 2314.585 676.8423) 
(list 2314.585 677.0193) 
(list 2240.5625 677.2693)))
(apply 'command (append '("pline") coords '("c")))
(setq currobj (ssadd (entlast) currobj))
(setq coords (list 
(list 2240.5625 677.4123) 
(list 2314.585 677.1623) 
(list 2314.585 677.3393) 
(list 2240.5625 677.4893)))
(apply 'command (append '("pline") coords '("c")))
(setq currobj (ssadd (entlast) currobj))
(setq coords (list 
(list 2240.5625 677.6323) 
(list 2314.585 677.4823) 
(list 2314.585 677.6593) 
(list 2240.5625 677.7093)))
(apply 'command (append '("pline") coords '("c")))
(setq currobj (ssadd (entlast) currobj))
(setq coords (list 
(list 2240.5625 677.8523) 
(list 2314.585 677.8023) 
(list 2314.585 677.9793) 
(list 2240.5625 677.9293)))
(apply 'command (append '("pline") coords '("c")))
(setq currobj (ssadd (entlast) currobj))
(setq coords (list 
(list 2240.5625 678.0723) 
(list 2314.585 678.1223) 
(list 2314.585 678.2993) 
(list 2240.5625 678.1493)))
(apply 'command (append '("pline") coords '("c")))
(setq currobj (ssadd (entlast) currobj))
(setq coords (list 
(list 2240.5625 678.2923) 
(list 2314.585 678.4423) 
(list 2314.585 678.6193) 
(list 2240.5625 678.3693)))
(apply 'command (append '("pline") coords '("c")))
(setq currobj (ssadd (entlast) currobj))
(setq coords (list 
(list 2240.5625 678.5123) 
(list 2314.585 678.7623) 
(list 2314.585 678.9393) 
(list 2240.5625 678.5893)))
(apply 'command (append '("pline") coords '("c")))
(setq currobj (ssadd (entlast) currobj))
(setq coords (list 
(list 2240.5625 678.7323) 
(list 2314.585 679.0823) 
(list 2314.585 679.2593) 
(list 2240.5625 678.8093)))
(apply 'command (append '("pline") coords '("c")))
(setq currobj (ssadd (entlast) currobj))
(setq coords (list 
(list 2240.5625 678.9523) 
(list 2314.585 679.4023) 
(list 2314.585 679.5793) 
(list 2240.5625 679.0293)))
(apply 'command (append '("pline") coords '("c")))
(setq currobj (ssadd (entlast) currobj))
(setq coords (list 
(list 2240.5625 679.1723) 
(list 2314.585 679.7223) 
(list 2314.585 679.8993) 
(list 2240.5625 679.2493)))
(apply 'command (append '("pline") coords '("c")))
(setq currobj (ssadd (entlast) currobj))
(setq coords (list 
(list 2240.5625 679.3923) 
(list 2314.585 680.0423) 
(list 2314.585 680.2193) 
(list 2240.5625 679.4693)))
(apply 'command (append '("pline") coords '("c")))
(setq currobj (ssadd (entlast) currobj))
(setq coords (list 
(list 2239.4375 679.4693) 
(list 2165.415 680.2193) 
(list 2165.415 680.0423) 
(list 2239.4375 679.3923)))
(apply 'command (append '("pline") coords '("c")))
(setq currobj (ssadd (entlast) currobj))
(setq coords (list 
(list 2239.4375 679.2493) 
(list 2165.415 679.8993) 
(list 2165.415 679.7223) 
(list 2239.4375 679.1723)))
(apply 'command (append '("pline") coords '("c")))
(setq currobj (ssadd (entlast) currobj))
(setq coords (list 
(list 2239.4375 679.0293) 
(list 2165.415 679.5793) 
(list 2165.415 679.4023) 
(list 2239.4375 678.9523)))
(apply 'command (append '("pline") coords '("c")))
(setq currobj (ssadd (entlast) currobj))
(setq coords (list 
(list 2239.4375 678.8093) 
(list 2165.415 679.2593) 
(list 2165.415 679.0823) 
(list 2239.4375 678.7323)))
(apply 'command (append '("pline") coords '("c")))
(setq currobj (ssadd (entlast) currobj))
(setq coords (list 
(list 2239.4375 678.5893) 
(list 2165.415 678.9393) 
(list 2165.415 678.7623) 
(list 2239.4375 678.5123)))
(apply 'command (append '("pline") coords '("c")))
(setq currobj (ssadd (entlast) currobj))
(setq coords (list 
(list 2239.4375 678.3693) 
(list 2165.415 678.6193) 
(list 2165.415 678.4423) 
(list 2239.4375 678.2923)))
(apply 'command (append '("pline") coords '("c")))
(setq currobj (ssadd (entlast) currobj))
(setq coords (list 
(list 2239.4375 678.1493) 
(list 2165.415 678.2993) 
(list 2165.415 678.1223) 
(list 2239.4375 678.0723)))
(apply 'command (append '("pline") coords '("c")))
(setq currobj (ssadd (entlast) currobj))
(setq coords (list 
(list 2239.4375 677.9293) 
(list 2165.415 677.9793) 
(list 2165.415 677.8023) 
(list 2239.4375 677.8523)))
(apply 'command (append '("pline") coords '("c")))
(setq currobj (ssadd (entlast) currobj))
(setq coords (list 
(list 2239.4375 677.7093) 
(list 2165.415 677.6593) 
(list 2165.415 677.4823) 
(list 2239.4375 677.6323)))
(apply 'command (append '("pline") coords '("c")))
(setq currobj (ssadd (entlast) currobj))
(setq coords (list 
(list 2239.4375 677.4893) 
(list 2165.415 677.3393) 
(list 2165.415 677.1623) 
(list 2239.4375 677.4123)))
(apply 'command (append '("pline") coords '("c")))
(setq currobj (ssadd (entlast) currobj))
(setq coords (list 
(list 2239.4375 677.2693) 
(list 2165.415 677.0193) 
(list 2165.415 676.8423) 
(list 2239.4375 677.1923)))
(apply 'command (append '("pline") coords '("c")))
(setq currobj (ssadd (entlast) currobj))
(setq coords (list 
(list 2239.4375 677.0493) 
(list 2165.415 676.6993) 
(list 2165.415 676.5223) 
(list 2239.4375 676.9723)))
(apply 'command (append '("pline") coords '("c")))
(setq currobj (ssadd (entlast) currobj))
(setq coords (list 
(list 2239.4375 676.8293) 
(list 2165.415 676.3793) 
(list 2165.415 676.2023) 
(list 2239.4375 676.7523)))
(apply 'command (append '("pline") coords '("c")))
(setq currobj (ssadd (entlast) currobj))
(setq coords (list 
(list 2239.4375 676.6093) 
(list 2165.415 676.0593) 
(list 2165.415 675.8823) 
(list 2239.4375 676.5323)))
(apply 'command (append '("pline") coords '("c")))
(setq currobj (ssadd (entlast) currobj))
(setq coords (list 
(list 2239.4375 676.3893) 
(list 2165.415 675.7393) 
(list 2165.415 675.5623) 
(list 2239.4375 676.3123)))
(apply 'command (append '("pline") coords '("c")))
(setq currobj (ssadd (entlast) currobj))
(command "_layer" "set" "nitride" "")
(command "_layer" "set" "text" "")
(command "_circle" "2239.0625,665.1693" "0.075")
(command "_circle" "2239.0625,665.4693" "0.075")
(command "_circle" "2239.0625,665.7693" "0.075")
(command "_circle" "2239.0625,666.0693" "0.075")
(command "_circle" "2239.0625,666.3693" "0.075")
(command "_circle" "2238.7625,665.1693" "0.075")
(command "_circle" "2238.7625,665.4693" "0.075")
(command "_circle" "2238.7625,665.7693" "0.075")
(command "_circle" "2238.7625,666.0693" "0.075")
(command "_circle" "2238.7625,666.3693" "0.075")
(command "_circle" "2238.4625,665.1693" "0.075")
(command "_circle" "2238.4625,665.4693" "0.075")
(command "_circle" "2238.4625,665.7693" "0.075")
(command "_circle" "2238.4625,666.0693" "0.075")
(command "_circle" "2238.4625,666.3693" "0.075")
(command "_circle" "2238.1625,665.1693" "0.075")
(command "_circle" "2238.1625,665.4693" "0.075")
(command "_circle" "2238.1625,665.7693" "0.075")
(command "_circle" "2238.1625,666.0693" "0.075")
(command "_circle" "2238.1625,666.3693" "0.075")
(command "_circle" "2237.8625,665.1693" "0.075")
(command "_circle" "2237.8625,665.4693" "0.075")
(command "_circle" "2237.8625,665.7693" "0.075")
(command "_circle" "2237.8625,666.0693" "0.075")
(command "_circle" "2237.8625,666.3693" "0.075")
(command "_layer" "set" "nitride" "")
(setq coords (list 
(list 2240.2625 690.6123) 
(list 2240.2625 806.257) 
(list 2239.7375 806.257) 
(list 2239.7375 690.6123)))
(apply 'command (append '("pline") coords '("c")))
(setq currobj (ssadd (entlast) currobj))
(command "_layer" "set" "prebias" "")
(command "_rectangle" "2239.7375,690.6123" "2240.2625,806.257")
(setq currobj (ssadd (entlast) currobj))
(command "_layer" "set" "nitride" "")
(setq coords (list 
(list 2240.2625 806.257) 
(list 2240.5625 816.257) 
(list 2240.5625 816.257) 
(list 2240.5625 817.257) 
(list 2314.585 816.507) 
(list 2314.585 821.45) 
(list 2240.5625 820.7) 
(list 2240.5625 821.7) 
(list 2240.5625 821.7) 
(list 2240.2625 831.7) 
(list 2239.7375 831.7) 
(list 2239.4375 821.7) 
(list 2239.4375 821.7) 
(list 2239.4375 820.7) 
(list 2165.415 821.45) 
(list 2165.415 816.507) 
(list 2239.4375 817.257) 
(list 2239.4375 816.257) 
(list 2239.4375 816.257) 
(list 2239.7375 806.257)))
(apply 'command (append '("pline") coords '("c")))
(setq currobj (ssadd (entlast) currobj))
(command "_layer" "set" "prebias" "")
(setq coords (list 
(list 2239.4375 806.257) 
(list 2239.4375 817.257) 
(list 2165.415 816.507) 
(list 2165.415 821.45) 
(list 2239.4375 820.7) 
(list 2239.4375 831.7) 
(list 2240.5625 831.7) 
(list 2240.5625 820.7) 
(list 2314.585 821.45) 
(list 2314.585 816.507) 
(list 2240.5625 817.257) 
(list 2240.5625 806.257)))
(apply 'command (append '("pline") coords '("c")))
(setq currobj (ssadd (entlast) currobj))
(command "_layer" "set" "nitride" "")
(command "_layer" "set" "fda1" "")
(setq coords (list 
(list 2240.5625 817.4) 
(list 2314.585 816.65) 
(list 2314.585 816.827) 
(list 2240.5625 817.477)))
(apply 'command (append '("pline") coords '("c")))
(setq currobj (ssadd (entlast) currobj))
(setq coords (list 
(list 2240.5625 817.62) 
(list 2314.585 816.97) 
(list 2314.585 817.147) 
(list 2240.5625 817.697)))
(apply 'command (append '("pline") coords '("c")))
(setq currobj (ssadd (entlast) currobj))
(setq coords (list 
(list 2240.5625 817.84) 
(list 2314.585 817.29) 
(list 2314.585 817.467) 
(list 2240.5625 817.917)))
(apply 'command (append '("pline") coords '("c")))
(setq currobj (ssadd (entlast) currobj))
(setq coords (list 
(list 2240.5625 818.06) 
(list 2314.585 817.61) 
(list 2314.585 817.787) 
(list 2240.5625 818.137)))
(apply 'command (append '("pline") coords '("c")))
(setq currobj (ssadd (entlast) currobj))
(setq coords (list 
(list 2240.5625 818.28) 
(list 2314.585 817.93) 
(list 2314.585 818.107) 
(list 2240.5625 818.357)))
(apply 'command (append '("pline") coords '("c")))
(setq currobj (ssadd (entlast) currobj))
(setq coords (list 
(list 2240.5625 818.5) 
(list 2314.585 818.25) 
(list 2314.585 818.427) 
(list 2240.5625 818.577)))
(apply 'command (append '("pline") coords '("c")))
(setq currobj (ssadd (entlast) currobj))
(setq coords (list 
(list 2240.5625 818.72) 
(list 2314.585 818.57) 
(list 2314.585 818.747) 
(list 2240.5625 818.797)))
(apply 'command (append '("pline") coords '("c")))
(setq currobj (ssadd (entlast) currobj))
(setq coords (list 
(list 2240.5625 818.94) 
(list 2314.585 818.89) 
(list 2314.585 819.067) 
(list 2240.5625 819.017)))
(apply 'command (append '("pline") coords '("c")))
(setq currobj (ssadd (entlast) currobj))
(setq coords (list 
(list 2240.5625 819.16) 
(list 2314.585 819.21) 
(list 2314.585 819.387) 
(list 2240.5625 819.237)))
(apply 'command (append '("pline") coords '("c")))
(setq currobj (ssadd (entlast) currobj))
(setq coords (list 
(list 2240.5625 819.38) 
(list 2314.585 819.53) 
(list 2314.585 819.707) 
(list 2240.5625 819.457)))
(apply 'command (append '("pline") coords '("c")))
(setq currobj (ssadd (entlast) currobj))
(setq coords (list 
(list 2240.5625 819.6) 
(list 2314.585 819.85) 
(list 2314.585 820.027) 
(list 2240.5625 819.677)))
(apply 'command (append '("pline") coords '("c")))
(setq currobj (ssadd (entlast) currobj))
(setq coords (list 
(list 2240.5625 819.82) 
(list 2314.585 820.17) 
(list 2314.585 820.347) 
(list 2240.5625 819.897)))
(apply 'command (append '("pline") coords '("c")))
(setq currobj (ssadd (entlast) currobj))
(setq coords (list 
(list 2240.5625 820.04) 
(list 2314.585 820.49) 
(list 2314.585 820.667) 
(list 2240.5625 820.117)))
(apply 'command (append '("pline") coords '("c")))
(setq currobj (ssadd (entlast) currobj))
(setq coords (list 
(list 2240.5625 820.26) 
(list 2314.585 820.81) 
(list 2314.585 820.987) 
(list 2240.5625 820.337)))
(apply 'command (append '("pline") coords '("c")))
(setq currobj (ssadd (entlast) currobj))
(setq coords (list 
(list 2240.5625 820.48) 
(list 2314.585 821.13) 
(list 2314.585 821.307) 
(list 2240.5625 820.557)))
(apply 'command (append '("pline") coords '("c")))
(setq currobj (ssadd (entlast) currobj))
(setq coords (list 
(list 2239.4375 820.557) 
(list 2165.415 821.307) 
(list 2165.415 821.13) 
(list 2239.4375 820.48)))
(apply 'command (append '("pline") coords '("c")))
(setq currobj (ssadd (entlast) currobj))
(setq coords (list 
(list 2239.4375 820.337) 
(list 2165.415 820.987) 
(list 2165.415 820.81) 
(list 2239.4375 820.26)))
(apply 'command (append '("pline") coords '("c")))
(setq currobj (ssadd (entlast) currobj))
(setq coords (list 
(list 2239.4375 820.117) 
(list 2165.415 820.667) 
(list 2165.415 820.49) 
(list 2239.4375 820.04)))
(apply 'command (append '("pline") coords '("c")))
(setq currobj (ssadd (entlast) currobj))
(setq coords (list 
(list 2239.4375 819.897) 
(list 2165.415 820.347) 
(list 2165.415 820.17) 
(list 2239.4375 819.82)))
(apply 'command (append '("pline") coords '("c")))
(setq currobj (ssadd (entlast) currobj))
(setq coords (list 
(list 2239.4375 819.677) 
(list 2165.415 820.027) 
(list 2165.415 819.85) 
(list 2239.4375 819.6)))
(apply 'command (append '("pline") coords '("c")))
(setq currobj (ssadd (entlast) currobj))
(setq coords (list 
(list 2239.4375 819.457) 
(list 2165.415 819.707) 
(list 2165.415 819.53) 
(list 2239.4375 819.38)))
(apply 'command (append '("pline") coords '("c")))
(setq currobj (ssadd (entlast) currobj))
(setq coords (list 
(list 2239.4375 819.237) 
(list 2165.415 819.387) 
(list 2165.415 819.21) 
(list 2239.4375 819.16)))
(apply 'command (append '("pline") coords '("c")))
(setq currobj (ssadd (entlast) currobj))
(setq coords (list 
(list 2239.4375 819.017) 
(list 2165.415 819.067) 
(list 2165.415 818.89) 
(list 2239.4375 818.94)))
(apply 'command (append '("pline") coords '("c")))
(setq currobj (ssadd (entlast) currobj))
(setq coords (list 
(list 2239.4375 818.797) 
(list 2165.415 818.747) 
(list 2165.415 818.57) 
(list 2239.4375 818.72)))
(apply 'command (append '("pline") coords '("c")))
(setq currobj (ssadd (entlast) currobj))
(setq coords (list 
(list 2239.4375 818.577) 
(list 2165.415 818.427) 
(list 2165.415 818.25) 
(list 2239.4375 818.5)))
(apply 'command (append '("pline") coords '("c")))
(setq currobj (ssadd (entlast) currobj))
(setq coords (list 
(list 2239.4375 818.357) 
(list 2165.415 818.107) 
(list 2165.415 817.93) 
(list 2239.4375 818.28)))
(apply 'command (append '("pline") coords '("c")))
(setq currobj (ssadd (entlast) currobj))
(setq coords (list 
(list 2239.4375 818.137) 
(list 2165.415 817.787) 
(list 2165.415 817.61) 
(list 2239.4375 818.06)))
(apply 'command (append '("pline") coords '("c")))
(setq currobj (ssadd (entlast) currobj))
(setq coords (list 
(list 2239.4375 817.917) 
(list 2165.415 817.467) 
(list 2165.415 817.29) 
(list 2239.4375 817.84)))
(apply 'command (append '("pline") coords '("c")))
(setq currobj (ssadd (entlast) currobj))
(setq coords (list 
(list 2239.4375 817.697) 
(list 2165.415 817.147) 
(list 2165.415 816.97) 
(list 2239.4375 817.62)))
(apply 'command (append '("pline") coords '("c")))
(setq currobj (ssadd (entlast) currobj))
(setq coords (list 
(list 2239.4375 817.477) 
(list 2165.415 816.827) 
(list 2165.415 816.65) 
(list 2239.4375 817.4)))
(apply 'command (append '("pline") coords '("c")))
(setq currobj (ssadd (entlast) currobj))
(command "_layer" "set" "nitride" "")
(command "_layer" "set" "text" "")
(command "_circle" "2239.0625,806.257" "0.075")
(command "_circle" "2239.0625,806.557" "0.075")
(command "_circle" "2239.0625,806.857" "0.075")
(command "_circle" "2239.0625,807.157" "0.075")
(command "_circle" "2239.0625,807.457" "0.075")
(command "_circle" "2238.7625,806.257" "0.075")
(command "_circle" "2238.7625,806.557" "0.075")
(command "_circle" "2238.7625,806.857" "0.075")
(command "_circle" "2238.7625,807.157" "0.075")
(command "_circle" "2238.7625,807.457" "0.075")
(command "_circle" "2238.4625,806.257" "0.075")
(command "_circle" "2238.4625,806.557" "0.075")
(command "_circle" "2238.4625,806.857" "0.075")
(command "_circle" "2238.4625,807.157" "0.075")
(command "_circle" "2238.4625,807.457" "0.075")
(command "_circle" "2238.1625,806.257" "0.075")
(command "_circle" "2238.1625,806.557" "0.075")
(command "_circle" "2238.1625,806.857" "0.075")
(command "_circle" "2238.1625,807.157" "0.075")
(command "_circle" "2238.1625,807.457" "0.075")
(command "_circle" "2237.8625,806.257" "0.075")
(command "_circle" "2237.8625,806.557" "0.075")
(command "_circle" "2237.8625,806.857" "0.075")
(command "_circle" "2237.8625,807.157" "0.075")
(command "_circle" "2237.8625,807.457" "0.075")
(command "_layer" "set" "nitride" "")
(setq coords (list 
(list 2240.2625 831.7) 
(list 2240.2625 836.7) 
(list 2239.7375 836.7) 
(list 2239.7375 831.7)))
(apply 'command (append '("pline") coords '("c")))
(setq currobj (ssadd (entlast) currobj))
(command "_layer" "set" "prebias" "")
(command "_rectangle" "2239.7375,831.7" "2240.2625,836.7")
(setq currobj (ssadd (entlast) currobj))
(command "_layer" "set" "nitride" "")
(setq cooledsinglenanobeam7 currobj)
(setq currobj nil)
(setq currobj (ssadd))
; DRAWING PHOTONIC CRYSTAL
(command "_layer" "set" "negYjunc" "")
(setq coords (list 
(list 2240.135 866.7) 
(list 2240 851.7) 
(list 2240 866.7)))
(apply 'command (append '("pline") coords '("c")))
(setq currobj (ssadd (entlast) currobj))
(setq coords (list 
(list 2240.2625 836.7) 
(list 2240.415 866.7) 
(list 2241.128 866.7) 
(list 2241.128 836.7)))
(apply 'command (append '("pline") coords '("c")))
(setq currobj (ssadd (entlast) currobj))
(setq coords (list 
(list 2239.865 866.7) 
(list 2240 851.7) 
(list 2240 866.7)))
(apply 'command (append '("pline") coords '("c")))
(setq currobj (ssadd (entlast) currobj))
(setq coords (list 
(list 2239.7375 836.7) 
(list 2239.585 866.7) 
(list 2238.872 866.7) 
(list 2238.872 836.7)))
(apply 'command (append '("pline") coords '("c")))
(setq currobj (ssadd (entlast) currobj))
(command "_layer" "set" "nitride" "")
(setq yjunction7 currobj)
(setq currobj nil)
(setq currobj (ssadd))
(setq tap7 nil)
(setq tap7 (ssadd))
(command "_layer" "set" "phc" "")
(setq coords (list 
(list 2240 866.7) 
(list 2240.135 866.7) 
(list 2240.135 866.7103) 
(list 2240.135 866.7206) 
(list 2240.135 866.7308) 
(list 2240.135 866.7411) 
(list 2240.135 866.7514) 
(list 2240.135 866.7617) 
(list 2240.135 866.7719) 
(list 2240.135 866.7822) 
(list 2240.135 866.7925) 
(list 2240.135 866.8028) 
(list 2240.135 866.8131) 
(list 2240.135 866.8233) 
(list 2240.135 866.8336) 
(list 2240.135 866.8439) 
(list 2240.135 866.8542) 
(list 2240.135 866.8644) 
(list 2240.135 866.8747) 
(list 2240.135 866.885) 
(list 2240.135 866.8953) 
(list 2240.135 866.9056) 
(list 2240.135 866.9158) 
(list 2240.135 866.9261) 
(list 2240.135 866.9364) 
(list 2240.135 866.9467) 
(list 2240.135 866.9569) 
(list 2240.135 866.9672) 
(list 2240.135 866.9775) 
(list 2240.135 866.9878) 
(list 2240.135 866.9981) 
(list 2240.135 867.0083) 
(list 2240.135 867.0186) 
(list 2240.135 867.0289) 
(list 2240.135 867.0392) 
(list 2240.135 867.0494) 
(list 2240.135 867.0597) 
(list 2240.135 867.07) 
(list 2240 867.07)))
(apply 'command (append '("pline") coords '("c")))
(setq tap7 (ssadd (entlast) tap7))
(command "_mirror" (entlast) "" "2240,900" "2240,901" "No")
(setq tap7 (ssadd (entlast) tap7))
(setq coords (list 
(list 2240.4249 866.7) 
(list 2240.415 866.7) 
(list 2240.4153 866.7103) 
(list 2240.4155 866.7206) 
(list 2240.4157 866.7308) 
(list 2240.4159 866.7411) 
(list 2240.4159 866.7514) 
(list 2240.4159 866.7617) 
(list 2240.4158 866.7719) 
(list 2240.4156 866.7822) 
(list 2240.4152 866.7925) 
(list 2240.4148 866.8028) 
(list 2240.4143 866.8131) 
(list 2240.4138 866.8233) 
(list 2240.4132 866.8336) 
(list 2240.4127 866.8439) 
(list 2240.4121 866.8542) 
(list 2240.4117 866.8644) 
(list 2240.4113 866.8747) 
(list 2240.411 866.885) 
(list 2240.4108 866.8953) 
(list 2240.4108 866.9056) 
(list 2240.411 866.9158) 
(list 2240.4114 866.9261) 
(list 2240.4119 866.9364) 
(list 2240.4126 866.9467) 
(list 2240.4135 866.9569) 
(list 2240.4145 866.9672) 
(list 2240.4157 866.9775) 
(list 2240.4169 866.9878) 
(list 2240.4182 866.9981) 
(list 2240.4195 867.0083) 
(list 2240.4208 867.0186) 
(list 2240.422 867.0289) 
(list 2240.423 867.0392) 
(list 2240.4239 867.0494) 
(list 2240.4245 867.0597) 
(list 2240.4249 867.07) 
(list 2240.4249 867.07)))
(apply 'command (append '("pline") coords '("c")))
(setq tap7 (ssadd (entlast) tap7))
(command "_mirror" (entlast) "" "2240,900" "2240,901" "No")
(setq tap7 (ssadd (entlast) tap7))
(setq coords (list 
(list 2241.128 866.7) 
(list 2240.4249 866.7) 
(list 2240.4249 866.7103) 
(list 2240.4249 866.7206) 
(list 2240.4249 866.7308) 
(list 2240.4249 866.7411) 
(list 2240.4249 866.7514) 
(list 2240.4249 866.7617) 
(list 2240.4249 866.7719) 
(list 2240.4249 866.7822) 
(list 2240.4249 866.7925) 
(list 2240.4249 866.8028) 
(list 2240.4249 866.8131) 
(list 2240.4249 866.8233) 
(list 2240.4249 866.8336) 
(list 2240.4249 866.8439) 
(list 2240.4249 866.8542) 
(list 2240.4249 866.8644) 
(list 2240.4249 866.8747) 
(list 2240.4249 866.885) 
(list 2240.4249 866.8953) 
(list 2240.4249 866.9056) 
(list 2240.4249 866.9158) 
(list 2240.4249 866.9261) 
(list 2240.4249 866.9364) 
(list 2240.4249 866.9467) 
(list 2240.4249 866.9569) 
(list 2240.4249 866.9672) 
(list 2240.4249 866.9775) 
(list 2240.4249 866.9878) 
(list 2240.4249 866.9981) 
(list 2240.4249 867.0083) 
(list 2240.4249 867.0186) 
(list 2240.4249 867.0289) 
(list 2240.4249 867.0392) 
(list 2240.4249 867.0494) 
(list 2240.4249 867.0597) 
(list 2240.4249 867.07) 
(list 2241.128 867.07)))
(apply 'command (append '("pline") coords '("c")))
(setq tap7 (ssadd (entlast) tap7))
(command "_mirror" (entlast) "" "2240,900" "2240,901" "No")
(setq tap7 (ssadd (entlast) tap7))
(setq coords (list 
(list 2240 867.07) 
(list 2240.135 867.07) 
(list 2240.135 867.0803) 
(list 2240.135 867.0906) 
(list 2240.135 867.1008) 
(list 2240.135 867.1111) 
(list 2240.135 867.1214) 
(list 2240.135 867.1317) 
(list 2240.135 867.1419) 
(list 2240.135 867.1522) 
(list 2240.135 867.1625) 
(list 2240.135 867.1728) 
(list 2240.135 867.1831) 
(list 2240.135 867.1933) 
(list 2240.135 867.2036) 
(list 2240.135 867.2139) 
(list 2240.135 867.2242) 
(list 2240.135 867.2344) 
(list 2240.135 867.2447) 
(list 2240.135 867.255) 
(list 2240.135 867.2653) 
(list 2240.135 867.2756) 
(list 2240.135 867.2858) 
(list 2240.135 867.2961) 
(list 2240.135 867.3064) 
(list 2240.135 867.3167) 
(list 2240.135 867.3269) 
(list 2240.135 867.3372) 
(list 2240.135 867.3475) 
(list 2240.135 867.3578) 
(list 2240.135 867.3681) 
(list 2240.135 867.3783) 
(list 2240.135 867.3886) 
(list 2240.135 867.3989) 
(list 2240.135 867.4092) 
(list 2240.135 867.4194) 
(list 2240.135 867.4297) 
(list 2240.135 867.44) 
(list 2240 867.44)))
(apply 'command (append '("pline") coords '("c")))
(setq tap7 (ssadd (entlast) tap7))
(command "_mirror" (entlast) "" "2240,900" "2240,901" "No")
(setq tap7 (ssadd (entlast) tap7))
(setq coords (list 
(list 2240.4349 867.07) 
(list 2240.4249 867.07) 
(list 2240.4251 867.0803) 
(list 2240.4249 867.0906) 
(list 2240.4245 867.1008) 
(list 2240.4237 867.1111) 
(list 2240.4227 867.1214) 
(list 2240.4213 867.1317) 
(list 2240.4198 867.1419) 
(list 2240.4181 867.1522) 
(list 2240.4162 867.1625) 
(list 2240.4142 867.1728) 
(list 2240.4122 867.1831) 
(list 2240.4102 867.1933) 
(list 2240.4084 867.2036) 
(list 2240.4067 867.2139) 
(list 2240.4053 867.2242) 
(list 2240.4041 867.2344) 
(list 2240.4033 867.2447) 
(list 2240.4029 867.255) 
(list 2240.4029 867.2653) 
(list 2240.4033 867.2756) 
(list 2240.4041 867.2858) 
(list 2240.4054 867.2961) 
(list 2240.407 867.3064) 
(list 2240.4091 867.3167) 
(list 2240.4114 867.3269) 
(list 2240.4139 867.3372) 
(list 2240.4166 867.3475) 
(list 2240.4194 867.3578) 
(list 2240.4222 867.3681) 
(list 2240.425 867.3783) 
(list 2240.4275 867.3886) 
(list 2240.4298 867.3989) 
(list 2240.4317 867.4092) 
(list 2240.4333 867.4194) 
(list 2240.4343 867.4297) 
(list 2240.4349 867.44) 
(list 2240.4349 867.44)))
(apply 'command (append '("pline") coords '("c")))
(setq tap7 (ssadd (entlast) tap7))
(command "_mirror" (entlast) "" "2240,900" "2240,901" "No")
(setq tap7 (ssadd (entlast) tap7))
(setq coords (list 
(list 2241.128 867.07) 
(list 2240.4349 867.07) 
(list 2240.4349 867.0803) 
(list 2240.4349 867.0906) 
(list 2240.4349 867.1008) 
(list 2240.4349 867.1111) 
(list 2240.4349 867.1214) 
(list 2240.4349 867.1317) 
(list 2240.4349 867.1419) 
(list 2240.4349 867.1522) 
(list 2240.4349 867.1625) 
(list 2240.4349 867.1728) 
(list 2240.4349 867.1831) 
(list 2240.4349 867.1933) 
(list 2240.4349 867.2036) 
(list 2240.4349 867.2139) 
(list 2240.4349 867.2242) 
(list 2240.4349 867.2344) 
(list 2240.4349 867.2447) 
(list 2240.4349 867.255) 
(list 2240.4349 867.2653) 
(list 2240.4349 867.2756) 
(list 2240.4349 867.2858) 
(list 2240.4349 867.2961) 
(list 2240.4349 867.3064) 
(list 2240.4349 867.3167) 
(list 2240.4349 867.3269) 
(list 2240.4349 867.3372) 
(list 2240.4349 867.3475) 
(list 2240.4349 867.3578) 
(list 2240.4349 867.3681) 
(list 2240.4349 867.3783) 
(list 2240.4349 867.3886) 
(list 2240.4349 867.3989) 
(list 2240.4349 867.4092) 
(list 2240.4349 867.4194) 
(list 2240.4349 867.4297) 
(list 2240.4349 867.44) 
(list 2241.128 867.44)))
(apply 'command (append '("pline") coords '("c")))
(setq tap7 (ssadd (entlast) tap7))
(command "_mirror" (entlast) "" "2240,900" "2240,901" "No")
(setq tap7 (ssadd (entlast) tap7))
(setq coords (list 
(list 2240 867.44) 
(list 2240.135 867.44) 
(list 2240.135 867.4503) 
(list 2240.135 867.4606) 
(list 2240.135 867.4708) 
(list 2240.135 867.4811) 
(list 2240.135 867.4914) 
(list 2240.135 867.5017) 
(list 2240.135 867.5119) 
(list 2240.135 867.5222) 
(list 2240.135 867.5325) 
(list 2240.135 867.5428) 
(list 2240.135 867.5531) 
(list 2240.135 867.5633) 
(list 2240.135 867.5736) 
(list 2240.135 867.5839) 
(list 2240.135 867.5942) 
(list 2240.135 867.6044) 
(list 2240.135 867.6147) 
(list 2240.135 867.625) 
(list 2240.135 867.6353) 
(list 2240.135 867.6456) 
(list 2240.135 867.6558) 
(list 2240.135 867.6661) 
(list 2240.135 867.6764) 
(list 2240.135 867.6867) 
(list 2240.135 867.6969) 
(list 2240.135 867.7072) 
(list 2240.135 867.7175) 
(list 2240.135 867.7278) 
(list 2240.135 867.7381) 
(list 2240.135 867.7483) 
(list 2240.135 867.7586) 
(list 2240.135 867.7689) 
(list 2240.135 867.7792) 
(list 2240.135 867.7894) 
(list 2240.135 867.7997) 
(list 2240.135 867.81) 
(list 2240 867.81)))
(apply 'command (append '("pline") coords '("c")))
(setq tap7 (ssadd (entlast) tap7))
(command "_mirror" (entlast) "" "2240,900" "2240,901" "No")
(setq tap7 (ssadd (entlast) tap7))
(setq coords (list 
(list 2240.4448 867.44) 
(list 2240.4349 867.44) 
(list 2240.4349 867.4503) 
(list 2240.4343 867.4606) 
(list 2240.4332 867.4708) 
(list 2240.4315 867.4811) 
(list 2240.4294 867.4914) 
(list 2240.4268 867.5017) 
(list 2240.4238 867.5119) 
(list 2240.4205 867.5222) 
(list 2240.4171 867.5325) 
(list 2240.4136 867.5428) 
(list 2240.4101 867.5531) 
(list 2240.4067 867.5633) 
(list 2240.4035 867.5736) 
(list 2240.4008 867.5839) 
(list 2240.3984 867.5942) 
(list 2240.3966 867.6044) 
(list 2240.3954 867.6147) 
(list 2240.3948 867.625) 
(list 2240.395 867.6353) 
(list 2240.3958 867.6456) 
(list 2240.3973 867.6558) 
(list 2240.3994 867.6661) 
(list 2240.4022 867.6764) 
(list 2240.4055 867.6867) 
(list 2240.4092 867.6969) 
(list 2240.4133 867.7072) 
(list 2240.4176 867.7175) 
(list 2240.4219 867.7278) 
(list 2240.4263 867.7381) 
(list 2240.4304 867.7483) 
(list 2240.4342 867.7586) 
(list 2240.4376 867.7689) 
(list 2240.4405 867.7792) 
(list 2240.4426 867.7894) 
(list 2240.4441 867.7997) 
(list 2240.4448 867.81) 
(list 2240.4448 867.81)))
(apply 'command (append '("pline") coords '("c")))
(setq tap7 (ssadd (entlast) tap7))
(command "_mirror" (entlast) "" "2240,900" "2240,901" "No")
(setq tap7 (ssadd (entlast) tap7))
(setq coords (list 
(list 2241.128 867.44) 
(list 2240.4448 867.44) 
(list 2240.4448 867.4503) 
(list 2240.4448 867.4606) 
(list 2240.4448 867.4708) 
(list 2240.4448 867.4811) 
(list 2240.4448 867.4914) 
(list 2240.4448 867.5017) 
(list 2240.4448 867.5119) 
(list 2240.4448 867.5222) 
(list 2240.4448 867.5325) 
(list 2240.4448 867.5428) 
(list 2240.4448 867.5531) 
(list 2240.4448 867.5633) 
(list 2240.4448 867.5736) 
(list 2240.4448 867.5839) 
(list 2240.4448 867.5942) 
(list 2240.4448 867.6044) 
(list 2240.4448 867.6147) 
(list 2240.4448 867.625) 
(list 2240.4448 867.6353) 
(list 2240.4448 867.6456) 
(list 2240.4448 867.6558) 
(list 2240.4448 867.6661) 
(list 2240.4448 867.6764) 
(list 2240.4448 867.6867) 
(list 2240.4448 867.6969) 
(list 2240.4448 867.7072) 
(list 2240.4448 867.7175) 
(list 2240.4448 867.7278) 
(list 2240.4448 867.7381) 
(list 2240.4448 867.7483) 
(list 2240.4448 867.7586) 
(list 2240.4448 867.7689) 
(list 2240.4448 867.7792) 
(list 2240.4448 867.7894) 
(list 2240.4448 867.7997) 
(list 2240.4448 867.81) 
(list 2241.128 867.81)))
(apply 'command (append '("pline") coords '("c")))
(setq tap7 (ssadd (entlast) tap7))
(command "_mirror" (entlast) "" "2240,900" "2240,901" "No")
(setq tap7 (ssadd (entlast) tap7))
(setq coords (list 
(list 2240 867.81) 
(list 2240.135 867.81) 
(list 2240.135 867.8203) 
(list 2240.135 867.8306) 
(list 2240.135 867.8408) 
(list 2240.135 867.8511) 
(list 2240.135 867.8614) 
(list 2240.135 867.8717) 
(list 2240.135 867.8819) 
(list 2240.135 867.8922) 
(list 2240.135 867.9025) 
(list 2240.135 867.9128) 
(list 2240.135 867.9231) 
(list 2240.135 867.9333) 
(list 2240.135 867.9436) 
(list 2240.135 867.9539) 
(list 2240.135 867.9642) 
(list 2240.135 867.9744) 
(list 2240.135 867.9847) 
(list 2240.135 867.995) 
(list 2240.135 868.0053) 
(list 2240.135 868.0156) 
(list 2240.135 868.0258) 
(list 2240.135 868.0361) 
(list 2240.135 868.0464) 
(list 2240.135 868.0567) 
(list 2240.135 868.0669) 
(list 2240.135 868.0772) 
(list 2240.135 868.0875) 
(list 2240.135 868.0978) 
(list 2240.135 868.1081) 
(list 2240.135 868.1183) 
(list 2240.135 868.1286) 
(list 2240.135 868.1389) 
(list 2240.135 868.1492) 
(list 2240.135 868.1594) 
(list 2240.135 868.1697) 
(list 2240.135 868.18) 
(list 2240 868.18)))
(apply 'command (append '("pline") coords '("c")))
(setq tap7 (ssadd (entlast) tap7))
(command "_mirror" (entlast) "" "2240,900" "2240,901" "No")
(setq tap7 (ssadd (entlast) tap7))
(setq coords (list 
(list 2240.4547 867.81) 
(list 2240.4448 867.81) 
(list 2240.4447 867.8203) 
(list 2240.4437 867.8306) 
(list 2240.4419 867.8408) 
(list 2240.4394 867.8511) 
(list 2240.4361 867.8614) 
(list 2240.4322 867.8717) 
(list 2240.4278 867.8819) 
(list 2240.423 867.8922) 
(list 2240.418 867.9025) 
(list 2240.4129 867.9128) 
(list 2240.4079 867.9231) 
(list 2240.4031 867.9333) 
(list 2240.3987 867.9436) 
(list 2240.3948 867.9539) 
(list 2240.3916 867.9642) 
(list 2240.3891 867.9744) 
(list 2240.3875 867.9847) 
(list 2240.3868 867.995) 
(list 2240.387 868.0053) 
(list 2240.3882 868.0156) 
(list 2240.3904 868.0258) 
(list 2240.3935 868.0361) 
(list 2240.3973 868.0464) 
(list 2240.4019 868.0567) 
(list 2240.4071 868.0669) 
(list 2240.4127 868.0772) 
(list 2240.4185 868.0875) 
(list 2240.4244 868.0978) 
(list 2240.4303 868.1081) 
(list 2240.4358 868.1183) 
(list 2240.4409 868.1286) 
(list 2240.4454 868.1389) 
(list 2240.4492 868.1492) 
(list 2240.452 868.1594) 
(list 2240.4539 868.1697) 
(list 2240.4547 868.18) 
(list 2240.4547 868.18)))
(apply 'command (append '("pline") coords '("c")))
(setq tap7 (ssadd (entlast) tap7))
(command "_mirror" (entlast) "" "2240,900" "2240,901" "No")
(setq tap7 (ssadd (entlast) tap7))
(setq coords (list 
(list 2241.128 867.81) 
(list 2240.4547 867.81) 
(list 2240.4547 867.8203) 
(list 2240.4547 867.8306) 
(list 2240.4547 867.8408) 
(list 2240.4547 867.8511) 
(list 2240.4547 867.8614) 
(list 2240.4547 867.8717) 
(list 2240.4547 867.8819) 
(list 2240.4547 867.8922) 
(list 2240.4547 867.9025) 
(list 2240.4547 867.9128) 
(list 2240.4547 867.9231) 
(list 2240.4547 867.9333) 
(list 2240.4547 867.9436) 
(list 2240.4547 867.9539) 
(list 2240.4547 867.9642) 
(list 2240.4547 867.9744) 
(list 2240.4547 867.9847) 
(list 2240.4547 867.995) 
(list 2240.4547 868.0053) 
(list 2240.4547 868.0156) 
(list 2240.4547 868.0258) 
(list 2240.4547 868.0361) 
(list 2240.4547 868.0464) 
(list 2240.4547 868.0567) 
(list 2240.4547 868.0669) 
(list 2240.4547 868.0772) 
(list 2240.4547 868.0875) 
(list 2240.4547 868.0978) 
(list 2240.4547 868.1081) 
(list 2240.4547 868.1183) 
(list 2240.4547 868.1286) 
(list 2240.4547 868.1389) 
(list 2240.4547 868.1492) 
(list 2240.4547 868.1594) 
(list 2240.4547 868.1697) 
(list 2240.4547 868.18) 
(list 2241.128 868.18)))
(apply 'command (append '("pline") coords '("c")))
(setq tap7 (ssadd (entlast) tap7))
(command "_mirror" (entlast) "" "2240,900" "2240,901" "No")
(setq tap7 (ssadd (entlast) tap7))
(setq coords (list 
(list 2240 868.18) 
(list 2240.135 868.18) 
(list 2240.135 868.1903) 
(list 2240.135 868.2006) 
(list 2240.135 868.2108) 
(list 2240.135 868.2211) 
(list 2240.135 868.2314) 
(list 2240.135 868.2417) 
(list 2240.135 868.2519) 
(list 2240.135 868.2622) 
(list 2240.135 868.2725) 
(list 2240.135 868.2828) 
(list 2240.135 868.2931) 
(list 2240.135 868.3033) 
(list 2240.135 868.3136) 
(list 2240.135 868.3239) 
(list 2240.135 868.3342) 
(list 2240.135 868.3444) 
(list 2240.135 868.3547) 
(list 2240.135 868.365) 
(list 2240.135 868.3753) 
(list 2240.135 868.3856) 
(list 2240.135 868.3958) 
(list 2240.135 868.4061) 
(list 2240.135 868.4164) 
(list 2240.135 868.4267) 
(list 2240.135 868.4369) 
(list 2240.135 868.4472) 
(list 2240.135 868.4575) 
(list 2240.135 868.4678) 
(list 2240.135 868.4781) 
(list 2240.135 868.4883) 
(list 2240.135 868.4986) 
(list 2240.135 868.5089) 
(list 2240.135 868.5192) 
(list 2240.135 868.5294) 
(list 2240.135 868.5397) 
(list 2240.135 868.55) 
(list 2240 868.55)))
(apply 'command (append '("pline") coords '("c")))
(setq tap7 (ssadd (entlast) tap7))
(command "_mirror" (entlast) "" "2240,900" "2240,901" "No")
(setq tap7 (ssadd (entlast) tap7))
(setq coords (list 
(list 2240.4647 868.18) 
(list 2240.4547 868.18) 
(list 2240.4545 868.1903) 
(list 2240.4531 868.2006) 
(list 2240.4506 868.2108) 
(list 2240.4472 868.2211) 
(list 2240.4428 868.2314) 
(list 2240.4376 868.2417) 
(list 2240.4318 868.2519) 
(list 2240.4255 868.2622) 
(list 2240.419 868.2725) 
(list 2240.4123 868.2828) 
(list 2240.4058 868.2931) 
(list 2240.3995 868.3033) 
(list 2240.3938 868.3136) 
(list 2240.3888 868.3239) 
(list 2240.3847 868.3342) 
(list 2240.3816 868.3444) 
(list 2240.3795 868.3547) 
(list 2240.3787 868.365) 
(list 2240.3791 868.3753) 
(list 2240.3807 868.3856) 
(list 2240.3836 868.3958) 
(list 2240.3875 868.4061) 
(list 2240.3925 868.4164) 
(list 2240.3984 868.4267) 
(list 2240.4049 868.4369) 
(list 2240.412 868.4472) 
(list 2240.4194 868.4575) 
(list 2240.4269 868.4678) 
(list 2240.4343 868.4781) 
(list 2240.4413 868.4883) 
(list 2240.4477 868.4986) 
(list 2240.4533 868.5089) 
(list 2240.4579 868.5192) 
(list 2240.4614 868.5294) 
(list 2240.4637 868.5397) 
(list 2240.4647 868.55) 
(list 2240.4647 868.55)))
(apply 'command (append '("pline") coords '("c")))
(setq tap7 (ssadd (entlast) tap7))
(command "_mirror" (entlast) "" "2240,900" "2240,901" "No")
(setq tap7 (ssadd (entlast) tap7))
(setq coords (list 
(list 2241.128 868.18) 
(list 2240.4647 868.18) 
(list 2240.4647 868.1903) 
(list 2240.4647 868.2006) 
(list 2240.4647 868.2108) 
(list 2240.4647 868.2211) 
(list 2240.4647 868.2314) 
(list 2240.4647 868.2417) 
(list 2240.4647 868.2519) 
(list 2240.4647 868.2622) 
(list 2240.4647 868.2725) 
(list 2240.4647 868.2828) 
(list 2240.4647 868.2931) 
(list 2240.4647 868.3033) 
(list 2240.4647 868.3136) 
(list 2240.4647 868.3239) 
(list 2240.4647 868.3342) 
(list 2240.4647 868.3444) 
(list 2240.4647 868.3547) 
(list 2240.4647 868.365) 
(list 2240.4647 868.3753) 
(list 2240.4647 868.3856) 
(list 2240.4647 868.3958) 
(list 2240.4647 868.4061) 
(list 2240.4647 868.4164) 
(list 2240.4647 868.4267) 
(list 2240.4647 868.4369) 
(list 2240.4647 868.4472) 
(list 2240.4647 868.4575) 
(list 2240.4647 868.4678) 
(list 2240.4647 868.4781) 
(list 2240.4647 868.4883) 
(list 2240.4647 868.4986) 
(list 2240.4647 868.5089) 
(list 2240.4647 868.5192) 
(list 2240.4647 868.5294) 
(list 2240.4647 868.5397) 
(list 2240.4647 868.55) 
(list 2241.128 868.55)))
(apply 'command (append '("pline") coords '("c")))
(setq tap7 (ssadd (entlast) tap7))
(command "_mirror" (entlast) "" "2240,900" "2240,901" "No")
(setq tap7 (ssadd (entlast) tap7))
(setq coords (list 
(list 2240 868.55) 
(list 2240.135 868.55) 
(list 2240.135 868.5603) 
(list 2240.135 868.5706) 
(list 2240.135 868.5808) 
(list 2240.135 868.5911) 
(list 2240.135 868.6014) 
(list 2240.135 868.6117) 
(list 2240.135 868.6219) 
(list 2240.135 868.6322) 
(list 2240.135 868.6425) 
(list 2240.135 868.6528) 
(list 2240.135 868.6631) 
(list 2240.135 868.6733) 
(list 2240.135 868.6836) 
(list 2240.135 868.6939) 
(list 2240.135 868.7042) 
(list 2240.135 868.7144) 
(list 2240.135 868.7247) 
(list 2240.135 868.735) 
(list 2240.135 868.7453) 
(list 2240.135 868.7556) 
(list 2240.135 868.7658) 
(list 2240.135 868.7761) 
(list 2240.135 868.7864) 
(list 2240.135 868.7967) 
(list 2240.135 868.8069) 
(list 2240.135 868.8172) 
(list 2240.135 868.8275) 
(list 2240.135 868.8378) 
(list 2240.135 868.8481) 
(list 2240.135 868.8583) 
(list 2240.135 868.8686) 
(list 2240.135 868.8789) 
(list 2240.135 868.8892) 
(list 2240.135 868.8994) 
(list 2240.135 868.9097) 
(list 2240.135 868.92) 
(list 2240 868.92)))
(apply 'command (append '("pline") coords '("c")))
(setq tap7 (ssadd (entlast) tap7))
(command "_mirror" (entlast) "" "2240,900" "2240,901" "No")
(setq tap7 (ssadd (entlast) tap7))
(setq coords (list 
(list 2240.4746 868.55) 
(list 2240.4647 868.55) 
(list 2240.4643 868.5603) 
(list 2240.4625 868.5706) 
(list 2240.4594 868.5808) 
(list 2240.455 868.5911) 
(list 2240.4495 868.6014) 
(list 2240.4431 868.6117) 
(list 2240.4358 868.6219) 
(list 2240.428 868.6322) 
(list 2240.4199 868.6425) 
(list 2240.4117 868.6528) 
(list 2240.4036 868.6631) 
(list 2240.396 868.6733) 
(list 2240.389 868.6836) 
(list 2240.3829 868.6939) 
(list 2240.3778 868.7042) 
(list 2240.374 868.7144) 
(list 2240.3716 868.7247) 
(list 2240.3706 868.735) 
(list 2240.3712 868.7453) 
(list 2240.3732 868.7556) 
(list 2240.3767 868.7658) 
(list 2240.3816 868.7761) 
(list 2240.3876 868.7864) 
(list 2240.3948 868.7967) 
(list 2240.4028 868.8069) 
(list 2240.4114 868.8172) 
(list 2240.4204 868.8275) 
(list 2240.4294 868.8378) 
(list 2240.4383 868.8481) 
(list 2240.4467 868.8583) 
(list 2240.4544 868.8686) 
(list 2240.4611 868.8789) 
(list 2240.4666 868.8892) 
(list 2240.4708 868.8994) 
(list 2240.4735 868.9097) 
(list 2240.4746 868.92) 
(list 2240.4746 868.92)))
(apply 'command (append '("pline") coords '("c")))
(setq tap7 (ssadd (entlast) tap7))
(command "_mirror" (entlast) "" "2240,900" "2240,901" "No")
(setq tap7 (ssadd (entlast) tap7))
(setq coords (list 
(list 2241.128 868.55) 
(list 2240.4746 868.55) 
(list 2240.4746 868.5603) 
(list 2240.4746 868.5706) 
(list 2240.4746 868.5808) 
(list 2240.4746 868.5911) 
(list 2240.4746 868.6014) 
(list 2240.4746 868.6117) 
(list 2240.4746 868.6219) 
(list 2240.4746 868.6322) 
(list 2240.4746 868.6425) 
(list 2240.4746 868.6528) 
(list 2240.4746 868.6631) 
(list 2240.4746 868.6733) 
(list 2240.4746 868.6836) 
(list 2240.4746 868.6939) 
(list 2240.4746 868.7042) 
(list 2240.4746 868.7144) 
(list 2240.4746 868.7247) 
(list 2240.4746 868.735) 
(list 2240.4746 868.7453) 
(list 2240.4746 868.7556) 
(list 2240.4746 868.7658) 
(list 2240.4746 868.7761) 
(list 2240.4746 868.7864) 
(list 2240.4746 868.7967) 
(list 2240.4746 868.8069) 
(list 2240.4746 868.8172) 
(list 2240.4746 868.8275) 
(list 2240.4746 868.8378) 
(list 2240.4746 868.8481) 
(list 2240.4746 868.8583) 
(list 2240.4746 868.8686) 
(list 2240.4746 868.8789) 
(list 2240.4746 868.8892) 
(list 2240.4746 868.8994) 
(list 2240.4746 868.9097) 
(list 2240.4746 868.92) 
(list 2241.128 868.92)))
(apply 'command (append '("pline") coords '("c")))
(setq tap7 (ssadd (entlast) tap7))
(command "_mirror" (entlast) "" "2240,900" "2240,901" "No")
(setq tap7 (ssadd (entlast) tap7))
(setq coords (list 
(list 2240 868.92) 
(list 2240.135 868.92) 
(list 2240.135 868.9303) 
(list 2240.135 868.9406) 
(list 2240.135 868.9508) 
(list 2240.135 868.9611) 
(list 2240.135 868.9714) 
(list 2240.135 868.9817) 
(list 2240.135 868.9919) 
(list 2240.135 869.0022) 
(list 2240.135 869.0125) 
(list 2240.135 869.0228) 
(list 2240.135 869.0331) 
(list 2240.135 869.0433) 
(list 2240.135 869.0536) 
(list 2240.135 869.0639) 
(list 2240.135 869.0742) 
(list 2240.135 869.0844) 
(list 2240.135 869.0947) 
(list 2240.135 869.105) 
(list 2240.135 869.1153) 
(list 2240.135 869.1256) 
(list 2240.135 869.1358) 
(list 2240.135 869.1461) 
(list 2240.135 869.1564) 
(list 2240.135 869.1667) 
(list 2240.135 869.1769) 
(list 2240.135 869.1872) 
(list 2240.135 869.1975) 
(list 2240.135 869.2078) 
(list 2240.135 869.2181) 
(list 2240.135 869.2283) 
(list 2240.135 869.2386) 
(list 2240.135 869.2489) 
(list 2240.135 869.2592) 
(list 2240.135 869.2694) 
(list 2240.135 869.2797) 
(list 2240.135 869.29) 
(list 2240 869.29)))
(apply 'command (append '("pline") coords '("c")))
(setq tap7 (ssadd (entlast) tap7))
(command "_mirror" (entlast) "" "2240,900" "2240,901" "No")
(setq tap7 (ssadd (entlast) tap7))
(setq coords (list 
(list 2240.4845 868.92) 
(list 2240.4746 868.92) 
(list 2240.4741 868.9303) 
(list 2240.4719 868.9406) 
(list 2240.4681 868.9508) 
(list 2240.4628 868.9611) 
(list 2240.4562 868.9714) 
(list 2240.4485 868.9817) 
(list 2240.4398 868.9919) 
(list 2240.4305 869.0022) 
(list 2240.4208 869.0125) 
(list 2240.411 869.0228) 
(list 2240.4015 869.0331) 
(list 2240.3924 869.0433) 
(list 2240.3841 869.0536) 
(list 2240.3769 869.0639) 
(list 2240.371 869.0742) 
(list 2240.3665 869.0844) 
(list 2240.3637 869.0947) 
(list 2240.3626 869.105) 
(list 2240.3632 869.1153) 
(list 2240.3657 869.1256) 
(list 2240.3698 869.1358) 
(list 2240.3756 869.1461) 
(list 2240.3828 869.1564) 
(list 2240.3912 869.1667) 
(list 2240.4006 869.1769) 
(list 2240.4108 869.1872) 
(list 2240.4213 869.1975) 
(list 2240.4319 869.2078) 
(list 2240.4423 869.2181) 
(list 2240.4521 869.2283) 
(list 2240.4611 869.2386) 
(list 2240.4689 869.2489) 
(list 2240.4754 869.2592) 
(list 2240.4802 869.2694) 
(list 2240.4833 869.2797) 
(list 2240.4845 869.29) 
(list 2240.4845 869.29)))
(apply 'command (append '("pline") coords '("c")))
(setq tap7 (ssadd (entlast) tap7))
(command "_mirror" (entlast) "" "2240,900" "2240,901" "No")
(setq tap7 (ssadd (entlast) tap7))
(setq coords (list 
(list 2241.128 868.92) 
(list 2240.4845 868.92) 
(list 2240.4845 868.9303) 
(list 2240.4845 868.9406) 
(list 2240.4845 868.9508) 
(list 2240.4845 868.9611) 
(list 2240.4845 868.9714) 
(list 2240.4845 868.9817) 
(list 2240.4845 868.9919) 
(list 2240.4845 869.0022) 
(list 2240.4845 869.0125) 
(list 2240.4845 869.0228) 
(list 2240.4845 869.0331) 
(list 2240.4845 869.0433) 
(list 2240.4845 869.0536) 
(list 2240.4845 869.0639) 
(list 2240.4845 869.0742) 
(list 2240.4845 869.0844) 
(list 2240.4845 869.0947) 
(list 2240.4845 869.105) 
(list 2240.4845 869.1153) 
(list 2240.4845 869.1256) 
(list 2240.4845 869.1358) 
(list 2240.4845 869.1461) 
(list 2240.4845 869.1564) 
(list 2240.4845 869.1667) 
(list 2240.4845 869.1769) 
(list 2240.4845 869.1872) 
(list 2240.4845 869.1975) 
(list 2240.4845 869.2078) 
(list 2240.4845 869.2181) 
(list 2240.4845 869.2283) 
(list 2240.4845 869.2386) 
(list 2240.4845 869.2489) 
(list 2240.4845 869.2592) 
(list 2240.4845 869.2694) 
(list 2240.4845 869.2797) 
(list 2240.4845 869.29) 
(list 2241.128 869.29)))
(apply 'command (append '("pline") coords '("c")))
(setq tap7 (ssadd (entlast) tap7))
(command "_mirror" (entlast) "" "2240,900" "2240,901" "No")
(setq tap7 (ssadd (entlast) tap7))
(setq coords (list 
(list 2240 869.29) 
(list 2240.135 869.29) 
(list 2240.135 869.3003) 
(list 2240.135 869.3106) 
(list 2240.135 869.3208) 
(list 2240.135 869.3311) 
(list 2240.135 869.3414) 
(list 2240.135 869.3517) 
(list 2240.135 869.3619) 
(list 2240.135 869.3722) 
(list 2240.135 869.3825) 
(list 2240.135 869.3928) 
(list 2240.135 869.4031) 
(list 2240.135 869.4133) 
(list 2240.135 869.4236) 
(list 2240.135 869.4339) 
(list 2240.135 869.4442) 
(list 2240.135 869.4544) 
(list 2240.135 869.4647) 
(list 2240.135 869.475) 
(list 2240.135 869.4853) 
(list 2240.135 869.4956) 
(list 2240.135 869.5058) 
(list 2240.135 869.5161) 
(list 2240.135 869.5264) 
(list 2240.135 869.5367) 
(list 2240.135 869.5469) 
(list 2240.135 869.5572) 
(list 2240.135 869.5675) 
(list 2240.135 869.5778) 
(list 2240.135 869.5881) 
(list 2240.135 869.5983) 
(list 2240.135 869.6086) 
(list 2240.135 869.6189) 
(list 2240.135 869.6292) 
(list 2240.135 869.6394) 
(list 2240.135 869.6497) 
(list 2240.135 869.66) 
(list 2240 869.66)))
(apply 'command (append '("pline") coords '("c")))
(setq tap7 (ssadd (entlast) tap7))
(command "_mirror" (entlast) "" "2240,900" "2240,901" "No")
(setq tap7 (ssadd (entlast) tap7))
(setq coords (list 
(list 2240.4945 869.29) 
(list 2240.4845 869.29) 
(list 2240.4838 869.3003) 
(list 2240.4813 869.3106) 
(list 2240.4768 869.3208) 
(list 2240.4707 869.3311) 
(list 2240.463 869.3414) 
(list 2240.4539 869.3517) 
(list 2240.4439 869.3619) 
(list 2240.433 869.3722) 
(list 2240.4218 869.3825) 
(list 2240.4104 869.3928) 
(list 2240.3993 869.4031) 
(list 2240.3888 869.4133) 
(list 2240.3793 869.4236) 
(list 2240.371 869.4339) 
(list 2240.3641 869.4442) 
(list 2240.359 869.4544) 
(list 2240.3557 869.4647) 
(list 2240.3545 869.475) 
(list 2240.3553 869.4853) 
(list 2240.3582 869.4956) 
(list 2240.363 869.5058) 
(list 2240.3696 869.5161) 
(list 2240.3779 869.5264) 
(list 2240.3877 869.5367) 
(list 2240.3985 869.5469) 
(list 2240.4101 869.5572) 
(list 2240.4222 869.5675) 
(list 2240.4344 869.5778) 
(list 2240.4463 869.5881) 
(list 2240.4576 869.5983) 
(list 2240.4678 869.6086) 
(list 2240.4768 869.6189) 
(list 2240.4841 869.6292) 
(list 2240.4896 869.6394) 
(list 2240.4931 869.6497) 
(list 2240.4945 869.66) 
(list 2240.4945 869.66)))
(apply 'command (append '("pline") coords '("c")))
(setq tap7 (ssadd (entlast) tap7))
(command "_mirror" (entlast) "" "2240,900" "2240,901" "No")
(setq tap7 (ssadd (entlast) tap7))
(setq coords (list 
(list 2241.128 869.29) 
(list 2240.4945 869.29) 
(list 2240.4945 869.3003) 
(list 2240.4945 869.3106) 
(list 2240.4945 869.3208) 
(list 2240.4945 869.3311) 
(list 2240.4945 869.3414) 
(list 2240.4945 869.3517) 
(list 2240.4945 869.3619) 
(list 2240.4945 869.3722) 
(list 2240.4945 869.3825) 
(list 2240.4945 869.3928) 
(list 2240.4945 869.4031) 
(list 2240.4945 869.4133) 
(list 2240.4945 869.4236) 
(list 2240.4945 869.4339) 
(list 2240.4945 869.4442) 
(list 2240.4945 869.4544) 
(list 2240.4945 869.4647) 
(list 2240.4945 869.475) 
(list 2240.4945 869.4853) 
(list 2240.4945 869.4956) 
(list 2240.4945 869.5058) 
(list 2240.4945 869.5161) 
(list 2240.4945 869.5264) 
(list 2240.4945 869.5367) 
(list 2240.4945 869.5469) 
(list 2240.4945 869.5572) 
(list 2240.4945 869.5675) 
(list 2240.4945 869.5778) 
(list 2240.4945 869.5881) 
(list 2240.4945 869.5983) 
(list 2240.4945 869.6086) 
(list 2240.4945 869.6189) 
(list 2240.4945 869.6292) 
(list 2240.4945 869.6394) 
(list 2240.4945 869.6497) 
(list 2240.4945 869.66) 
(list 2241.128 869.66)))
(apply 'command (append '("pline") coords '("c")))
(setq tap7 (ssadd (entlast) tap7))
(command "_mirror" (entlast) "" "2240,900" "2240,901" "No")
(setq tap7 (ssadd (entlast) tap7))
(setq coords (list 
(list 2240 869.66) 
(list 2240.135 869.66) 
(list 2240.135 869.6703) 
(list 2240.135 869.6806) 
(list 2240.135 869.6908) 
(list 2240.135 869.7011) 
(list 2240.135 869.7114) 
(list 2240.135 869.7217) 
(list 2240.135 869.7319) 
(list 2240.135 869.7422) 
(list 2240.135 869.7525) 
(list 2240.135 869.7628) 
(list 2240.135 869.7731) 
(list 2240.135 869.7833) 
(list 2240.135 869.7936) 
(list 2240.135 869.8039) 
(list 2240.135 869.8142) 
(list 2240.135 869.8244) 
(list 2240.135 869.8347) 
(list 2240.135 869.845) 
(list 2240.135 869.8553) 
(list 2240.135 869.8656) 
(list 2240.135 869.8758) 
(list 2240.135 869.8861) 
(list 2240.135 869.8964) 
(list 2240.135 869.9067) 
(list 2240.135 869.9169) 
(list 2240.135 869.9272) 
(list 2240.135 869.9375) 
(list 2240.135 869.9478) 
(list 2240.135 869.9581) 
(list 2240.135 869.9683) 
(list 2240.135 869.9786) 
(list 2240.135 869.9889) 
(list 2240.135 869.9992) 
(list 2240.135 870.0094) 
(list 2240.135 870.0197) 
(list 2240.135 870.03) 
(list 2240 870.03)))
(apply 'command (append '("pline") coords '("c")))
(setq tap7 (ssadd (entlast) tap7))
(command "_mirror" (entlast) "" "2240,900" "2240,901" "No")
(setq tap7 (ssadd (entlast) tap7))
(setq coords (list 
(list 2240.5044 869.66) 
(list 2240.4945 869.66) 
(list 2240.4936 869.6703) 
(list 2240.4906 869.6806) 
(list 2240.4855 869.6908) 
(list 2240.4785 869.7011) 
(list 2240.4697 869.7114) 
(list 2240.4594 869.7217) 
(list 2240.4479 869.7319) 
(list 2240.4355 869.7422) 
(list 2240.4227 869.7525) 
(list 2240.4098 869.7628) 
(list 2240.3972 869.7731) 
(list 2240.3853 869.7833) 
(list 2240.3744 869.7936) 
(list 2240.365 869.8039) 
(list 2240.3573 869.8142) 
(list 2240.3515 869.8244) 
(list 2240.3478 869.8347) 
(list 2240.3464 869.845) 
(list 2240.3474 869.8553) 
(list 2240.3506 869.8656) 
(list 2240.3561 869.8758) 
(list 2240.3637 869.8861) 
(list 2240.3731 869.8964) 
(list 2240.3841 869.9067) 
(list 2240.3964 869.9169) 
(list 2240.4095 869.9272) 
(list 2240.4232 869.9375) 
(list 2240.4369 869.9478) 
(list 2240.4503 869.9581) 
(list 2240.463 869.9683) 
(list 2240.4745 869.9786) 
(list 2240.4846 869.9889) 
(list 2240.4928 869.9992) 
(list 2240.499 870.0094) 
(list 2240.5029 870.0197) 
(list 2240.5044 870.03) 
(list 2240.5044 870.03)))
(apply 'command (append '("pline") coords '("c")))
(setq tap7 (ssadd (entlast) tap7))
(command "_mirror" (entlast) "" "2240,900" "2240,901" "No")
(setq tap7 (ssadd (entlast) tap7))
(setq coords (list 
(list 2241.128 869.66) 
(list 2240.5044 869.66) 
(list 2240.5044 869.6703) 
(list 2240.5044 869.6806) 
(list 2240.5044 869.6908) 
(list 2240.5044 869.7011) 
(list 2240.5044 869.7114) 
(list 2240.5044 869.7217) 
(list 2240.5044 869.7319) 
(list 2240.5044 869.7422) 
(list 2240.5044 869.7525) 
(list 2240.5044 869.7628) 
(list 2240.5044 869.7731) 
(list 2240.5044 869.7833) 
(list 2240.5044 869.7936) 
(list 2240.5044 869.8039) 
(list 2240.5044 869.8142) 
(list 2240.5044 869.8244) 
(list 2240.5044 869.8347) 
(list 2240.5044 869.845) 
(list 2240.5044 869.8553) 
(list 2240.5044 869.8656) 
(list 2240.5044 869.8758) 
(list 2240.5044 869.8861) 
(list 2240.5044 869.8964) 
(list 2240.5044 869.9067) 
(list 2240.5044 869.9169) 
(list 2240.5044 869.9272) 
(list 2240.5044 869.9375) 
(list 2240.5044 869.9478) 
(list 2240.5044 869.9581) 
(list 2240.5044 869.9683) 
(list 2240.5044 869.9786) 
(list 2240.5044 869.9889) 
(list 2240.5044 869.9992) 
(list 2240.5044 870.0094) 
(list 2240.5044 870.0197) 
(list 2240.5044 870.03) 
(list 2241.128 870.03)))
(apply 'command (append '("pline") coords '("c")))
(setq tap7 (ssadd (entlast) tap7))
(command "_mirror" (entlast) "" "2240,900" "2240,901" "No")
(setq tap7 (ssadd (entlast) tap7))
(setq coords (list 
(list 2240 870.03) 
(list 2240.135 870.03) 
(list 2240.135 870.0403) 
(list 2240.135 870.0506) 
(list 2240.135 870.0608) 
(list 2240.135 870.0711) 
(list 2240.135 870.0814) 
(list 2240.135 870.0917) 
(list 2240.135 870.1019) 
(list 2240.135 870.1122) 
(list 2240.135 870.1225) 
(list 2240.135 870.1328) 
(list 2240.135 870.1431) 
(list 2240.135 870.1533) 
(list 2240.135 870.1636) 
(list 2240.135 870.1739) 
(list 2240.135 870.1842) 
(list 2240.135 870.1944) 
(list 2240.135 870.2047) 
(list 2240.135 870.215) 
(list 2240.135 870.2253) 
(list 2240.135 870.2356) 
(list 2240.135 870.2458) 
(list 2240.135 870.2561) 
(list 2240.135 870.2664) 
(list 2240.135 870.2767) 
(list 2240.135 870.2869) 
(list 2240.135 870.2972) 
(list 2240.135 870.3075) 
(list 2240.135 870.3178) 
(list 2240.135 870.3281) 
(list 2240.135 870.3383) 
(list 2240.135 870.3486) 
(list 2240.135 870.3589) 
(list 2240.135 870.3692) 
(list 2240.135 870.3794) 
(list 2240.135 870.3897) 
(list 2240.135 870.4) 
(list 2240 870.4)))
(apply 'command (append '("pline") coords '("c")))
(setq tap7 (ssadd (entlast) tap7))
(command "_mirror" (entlast) "" "2240,900" "2240,901" "No")
(setq tap7 (ssadd (entlast) tap7))
(setq coords (list 
(list 2240.5143 870.03) 
(list 2240.5044 870.03) 
(list 2240.5034 870.0403) 
(list 2240.5 870.0506) 
(list 2240.4943 870.0608) 
(list 2240.4863 870.0711) 
(list 2240.4764 870.0814) 
(list 2240.4648 870.0917) 
(list 2240.4519 870.1019) 
(list 2240.438 870.1122) 
(list 2240.4236 870.1225) 
(list 2240.4092 870.1328) 
(list 2240.395 870.1431) 
(list 2240.3817 870.1533) 
(list 2240.3696 870.1636) 
(list 2240.359 870.1739) 
(list 2240.3504 870.1842) 
(list 2240.3439 870.1944) 
(list 2240.3399 870.2047) 
(list 2240.3384 870.215) 
(list 2240.3394 870.2253) 
(list 2240.3431 870.2356) 
(list 2240.3493 870.2458) 
(list 2240.3577 870.2561) 
(list 2240.3682 870.2664) 
(list 2240.3805 870.2767) 
(list 2240.3942 870.2869) 
(list 2240.4089 870.2972) 
(list 2240.4241 870.3075) 
(list 2240.4394 870.3178) 
(list 2240.4543 870.3281) 
(list 2240.4684 870.3383) 
(list 2240.4813 870.3486) 
(list 2240.4924 870.3589) 
(list 2240.5015 870.3692) 
(list 2240.5084 870.3794) 
(list 2240.5127 870.3897) 
(list 2240.5143 870.4) 
(list 2240.5143 870.4)))
(apply 'command (append '("pline") coords '("c")))
(setq tap7 (ssadd (entlast) tap7))
(command "_mirror" (entlast) "" "2240,900" "2240,901" "No")
(setq tap7 (ssadd (entlast) tap7))
(setq coords (list 
(list 2241.128 870.03) 
(list 2240.5143 870.03) 
(list 2240.5143 870.0403) 
(list 2240.5143 870.0506) 
(list 2240.5143 870.0608) 
(list 2240.5143 870.0711) 
(list 2240.5143 870.0814) 
(list 2240.5143 870.0917) 
(list 2240.5143 870.1019) 
(list 2240.5143 870.1122) 
(list 2240.5143 870.1225) 
(list 2240.5143 870.1328) 
(list 2240.5143 870.1431) 
(list 2240.5143 870.1533) 
(list 2240.5143 870.1636) 
(list 2240.5143 870.1739) 
(list 2240.5143 870.1842) 
(list 2240.5143 870.1944) 
(list 2240.5143 870.2047) 
(list 2240.5143 870.215) 
(list 2240.5143 870.2253) 
(list 2240.5143 870.2356) 
(list 2240.5143 870.2458) 
(list 2240.5143 870.2561) 
(list 2240.5143 870.2664) 
(list 2240.5143 870.2767) 
(list 2240.5143 870.2869) 
(list 2240.5143 870.2972) 
(list 2240.5143 870.3075) 
(list 2240.5143 870.3178) 
(list 2240.5143 870.3281) 
(list 2240.5143 870.3383) 
(list 2240.5143 870.3486) 
(list 2240.5143 870.3589) 
(list 2240.5143 870.3692) 
(list 2240.5143 870.3794) 
(list 2240.5143 870.3897) 
(list 2240.5143 870.4) 
(list 2241.128 870.4)))
(apply 'command (append '("pline") coords '("c")))
(setq tap7 (ssadd (entlast) tap7))
(command "_mirror" (entlast) "" "2240,900" "2240,901" "No")
(setq tap7 (ssadd (entlast) tap7))
(setq coords (list 
(list 2240 870.4) 
(list 2240.135 870.4) 
(list 2240.135 870.4103) 
(list 2240.135 870.4206) 
(list 2240.135 870.4308) 
(list 2240.135 870.4411) 
(list 2240.135 870.4514) 
(list 2240.135 870.4617) 
(list 2240.135 870.4719) 
(list 2240.135 870.4822) 
(list 2240.135 870.4925) 
(list 2240.135 870.5028) 
(list 2240.135 870.5131) 
(list 2240.135 870.5233) 
(list 2240.135 870.5336) 
(list 2240.135 870.5439) 
(list 2240.135 870.5542) 
(list 2240.135 870.5644) 
(list 2240.135 870.5747) 
(list 2240.135 870.585) 
(list 2240.135 870.5953) 
(list 2240.135 870.6056) 
(list 2240.135 870.6158) 
(list 2240.135 870.6261) 
(list 2240.135 870.6364) 
(list 2240.135 870.6467) 
(list 2240.135 870.6569) 
(list 2240.135 870.6672) 
(list 2240.135 870.6775) 
(list 2240.135 870.6878) 
(list 2240.135 870.6981) 
(list 2240.135 870.7083) 
(list 2240.135 870.7186) 
(list 2240.135 870.7289) 
(list 2240.135 870.7392) 
(list 2240.135 870.7494) 
(list 2240.135 870.7597) 
(list 2240.135 870.77) 
(list 2240 870.77)))
(apply 'command (append '("pline") coords '("c")))
(setq tap7 (ssadd (entlast) tap7))
(command "_mirror" (entlast) "" "2240,900" "2240,901" "No")
(setq tap7 (ssadd (entlast) tap7))
(setq coords (list 
(list 2240.5243 870.4) 
(list 2240.5143 870.4) 
(list 2240.5132 870.4103) 
(list 2240.5094 870.4206) 
(list 2240.503 870.4308) 
(list 2240.4941 870.4411) 
(list 2240.4831 870.4514) 
(list 2240.4702 870.4617) 
(list 2240.4559 870.4719) 
(list 2240.4405 870.4822) 
(list 2240.4246 870.4925) 
(list 2240.4085 870.5028) 
(list 2240.3929 870.5131) 
(list 2240.3781 870.5233) 
(list 2240.3647 870.5336) 
(list 2240.3531 870.5439) 
(list 2240.3435 870.5542) 
(list 2240.3364 870.5644) 
(list 2240.332 870.5747) 
(list 2240.3303 870.585) 
(list 2240.3315 870.5953) 
(list 2240.3356 870.6056) 
(list 2240.3424 870.6158) 
(list 2240.3517 870.6261) 
(list 2240.3634 870.6364) 
(list 2240.377 870.6467) 
(list 2240.3921 870.6569) 
(list 2240.4082 870.6672) 
(list 2240.425 870.6775) 
(list 2240.4419 870.6878) 
(list 2240.4583 870.6981) 
(list 2240.4739 870.7083) 
(list 2240.488 870.7186) 
(list 2240.5002 870.7289) 
(list 2240.5103 870.7392) 
(list 2240.5178 870.7494) 
(list 2240.5225 870.7597) 
(list 2240.5243 870.77) 
(list 2240.5243 870.77)))
(apply 'command (append '("pline") coords '("c")))
(setq tap7 (ssadd (entlast) tap7))
(command "_mirror" (entlast) "" "2240,900" "2240,901" "No")
(setq tap7 (ssadd (entlast) tap7))
(setq coords (list 
(list 2241.128 870.4) 
(list 2240.5243 870.4) 
(list 2240.5243 870.4103) 
(list 2240.5243 870.4206) 
(list 2240.5243 870.4308) 
(list 2240.5243 870.4411) 
(list 2240.5243 870.4514) 
(list 2240.5243 870.4617) 
(list 2240.5243 870.4719) 
(list 2240.5243 870.4822) 
(list 2240.5243 870.4925) 
(list 2240.5243 870.5028) 
(list 2240.5243 870.5131) 
(list 2240.5243 870.5233) 
(list 2240.5243 870.5336) 
(list 2240.5243 870.5439) 
(list 2240.5243 870.5542) 
(list 2240.5243 870.5644) 
(list 2240.5243 870.5747) 
(list 2240.5243 870.585) 
(list 2240.5243 870.5953) 
(list 2240.5243 870.6056) 
(list 2240.5243 870.6158) 
(list 2240.5243 870.6261) 
(list 2240.5243 870.6364) 
(list 2240.5243 870.6467) 
(list 2240.5243 870.6569) 
(list 2240.5243 870.6672) 
(list 2240.5243 870.6775) 
(list 2240.5243 870.6878) 
(list 2240.5243 870.6981) 
(list 2240.5243 870.7083) 
(list 2240.5243 870.7186) 
(list 2240.5243 870.7289) 
(list 2240.5243 870.7392) 
(list 2240.5243 870.7494) 
(list 2240.5243 870.7597) 
(list 2240.5243 870.77) 
(list 2241.128 870.77)))
(apply 'command (append '("pline") coords '("c")))
(setq tap7 (ssadd (entlast) tap7))
(command "_mirror" (entlast) "" "2240,900" "2240,901" "No")
(setq tap7 (ssadd (entlast) tap7))
(setq coords (list 
(list 2240 870.77) 
(list 2240.135 870.77) 
(list 2240.135 870.7803) 
(list 2240.135 870.7906) 
(list 2240.135 870.8008) 
(list 2240.135 870.8111) 
(list 2240.135 870.8214) 
(list 2240.135 870.8317) 
(list 2240.135 870.8419) 
(list 2240.135 870.8522) 
(list 2240.135 870.8625) 
(list 2240.135 870.8728) 
(list 2240.135 870.8831) 
(list 2240.135 870.8933) 
(list 2240.135 870.9036) 
(list 2240.135 870.9139) 
(list 2240.135 870.9242) 
(list 2240.135 870.9344) 
(list 2240.135 870.9447) 
(list 2240.135 870.955) 
(list 2240.135 870.9653) 
(list 2240.135 870.9756) 
(list 2240.135 870.9858) 
(list 2240.135 870.9961) 
(list 2240.135 871.0064) 
(list 2240.135 871.0167) 
(list 2240.135 871.0269) 
(list 2240.135 871.0372) 
(list 2240.135 871.0475) 
(list 2240.135 871.0578) 
(list 2240.135 871.0681) 
(list 2240.135 871.0783) 
(list 2240.135 871.0886) 
(list 2240.135 871.0989) 
(list 2240.135 871.1092) 
(list 2240.135 871.1194) 
(list 2240.135 871.1297) 
(list 2240.135 871.14) 
(list 2240 871.14)))
(apply 'command (append '("pline") coords '("c")))
(setq tap7 (ssadd (entlast) tap7))
(command "_mirror" (entlast) "" "2240,900" "2240,901" "No")
(setq tap7 (ssadd (entlast) tap7))
(setq coords (list 
(list 2240.5342 870.77) 
(list 2240.5243 870.77) 
(list 2240.523 870.7803) 
(list 2240.5188 870.7906) 
(list 2240.5117 870.8008) 
(list 2240.502 870.8111) 
(list 2240.4898 870.8214) 
(list 2240.4757 870.8317) 
(list 2240.4599 870.8419) 
(list 2240.443 870.8522) 
(list 2240.4255 870.8625) 
(list 2240.4079 870.8728) 
(list 2240.3908 870.8831) 
(list 2240.3746 870.8933) 
(list 2240.3599 870.9036) 
(list 2240.3471 870.9139) 
(list 2240.3367 870.9242) 
(list 2240.3289 870.9344) 
(list 2240.324 870.9447) 
(list 2240.3222 870.955) 
(list 2240.3236 870.9653) 
(list 2240.3281 870.9756) 
(list 2240.3355 870.9858) 
(list 2240.3458 870.9961) 
(list 2240.3585 871.0064) 
(list 2240.3734 871.0167) 
(list 2240.3899 871.0269) 
(list 2240.4076 871.0372) 
(list 2240.426 871.0475) 
(list 2240.4444 871.0578) 
(list 2240.4624 871.0681) 
(list 2240.4793 871.0783) 
(list 2240.4947 871.0886) 
(list 2240.5081 871.0989) 
(list 2240.519 871.1092) 
(list 2240.5272 871.1194) 
(list 2240.5323 871.1297) 
(list 2240.5342 871.14) 
(list 2240.5342 871.14)))
(apply 'command (append '("pline") coords '("c")))
(setq tap7 (ssadd (entlast) tap7))
(command "_mirror" (entlast) "" "2240,900" "2240,901" "No")
(setq tap7 (ssadd (entlast) tap7))
(setq coords (list 
(list 2241.128 870.77) 
(list 2240.5342 870.77) 
(list 2240.5342 870.7803) 
(list 2240.5342 870.7906) 
(list 2240.5342 870.8008) 
(list 2240.5342 870.8111) 
(list 2240.5342 870.8214) 
(list 2240.5342 870.8317) 
(list 2240.5342 870.8419) 
(list 2240.5342 870.8522) 
(list 2240.5342 870.8625) 
(list 2240.5342 870.8728) 
(list 2240.5342 870.8831) 
(list 2240.5342 870.8933) 
(list 2240.5342 870.9036) 
(list 2240.5342 870.9139) 
(list 2240.5342 870.9242) 
(list 2240.5342 870.9344) 
(list 2240.5342 870.9447) 
(list 2240.5342 870.955) 
(list 2240.5342 870.9653) 
(list 2240.5342 870.9756) 
(list 2240.5342 870.9858) 
(list 2240.5342 870.9961) 
(list 2240.5342 871.0064) 
(list 2240.5342 871.0167) 
(list 2240.5342 871.0269) 
(list 2240.5342 871.0372) 
(list 2240.5342 871.0475) 
(list 2240.5342 871.0578) 
(list 2240.5342 871.0681) 
(list 2240.5342 871.0783) 
(list 2240.5342 871.0886) 
(list 2240.5342 871.0989) 
(list 2240.5342 871.1092) 
(list 2240.5342 871.1194) 
(list 2240.5342 871.1297) 
(list 2240.5342 871.14) 
(list 2241.128 871.14)))
(apply 'command (append '("pline") coords '("c")))
(setq tap7 (ssadd (entlast) tap7))
(command "_mirror" (entlast) "" "2240,900" "2240,901" "No")
(setq tap7 (ssadd (entlast) tap7))
(setq coords (list 
(list 2240 871.14) 
(list 2240.135 871.14) 
(list 2240.135 871.1503) 
(list 2240.135 871.1606) 
(list 2240.135 871.1708) 
(list 2240.135 871.1811) 
(list 2240.135 871.1914) 
(list 2240.135 871.2017) 
(list 2240.135 871.2119) 
(list 2240.135 871.2222) 
(list 2240.135 871.2325) 
(list 2240.135 871.2428) 
(list 2240.135 871.2531) 
(list 2240.135 871.2633) 
(list 2240.135 871.2736) 
(list 2240.135 871.2839) 
(list 2240.135 871.2942) 
(list 2240.135 871.3044) 
(list 2240.135 871.3147) 
(list 2240.135 871.325) 
(list 2240.135 871.3353) 
(list 2240.135 871.3456) 
(list 2240.135 871.3558) 
(list 2240.135 871.3661) 
(list 2240.135 871.3764) 
(list 2240.135 871.3867) 
(list 2240.135 871.3969) 
(list 2240.135 871.4072) 
(list 2240.135 871.4175) 
(list 2240.135 871.4278) 
(list 2240.135 871.4381) 
(list 2240.135 871.4483) 
(list 2240.135 871.4586) 
(list 2240.135 871.4689) 
(list 2240.135 871.4792) 
(list 2240.135 871.4894) 
(list 2240.135 871.4997) 
(list 2240.135 871.51) 
(list 2240 871.51)))
(apply 'command (append '("pline") coords '("c")))
(setq tap7 (ssadd (entlast) tap7))
(command "_mirror" (entlast) "" "2240,900" "2240,901" "No")
(setq tap7 (ssadd (entlast) tap7))
(setq coords (list 
(list 2240.5441 871.14) 
(list 2240.5342 871.14) 
(list 2240.5328 871.1503) 
(list 2240.5282 871.1606) 
(list 2240.5205 871.1708) 
(list 2240.5098 871.1811) 
(list 2240.4966 871.1914) 
(list 2240.4811 871.2017) 
(list 2240.4639 871.2119) 
(list 2240.4455 871.2222) 
(list 2240.4264 871.2325) 
(list 2240.4073 871.2428) 
(list 2240.3886 871.2531) 
(list 2240.371 871.2633) 
(list 2240.355 871.2736) 
(list 2240.3411 871.2839) 
(list 2240.3298 871.2942) 
(list 2240.3214 871.3044) 
(list 2240.3161 871.3147) 
(list 2240.3142 871.325) 
(list 2240.3157 871.3353) 
(list 2240.3205 871.3456) 
(list 2240.3287 871.3558) 
(list 2240.3398 871.3661) 
(list 2240.3537 871.3764) 
(list 2240.3698 871.3867) 
(list 2240.3878 871.3969) 
(list 2240.407 871.4072) 
(list 2240.4269 871.4175) 
(list 2240.4469 871.4278) 
(list 2240.4664 871.4381) 
(list 2240.4847 871.4483) 
(list 2240.5014 871.4586) 
(list 2240.5159 871.4689) 
(list 2240.5277 871.4792) 
(list 2240.5366 871.4894) 
(list 2240.5421 871.4997) 
(list 2240.5441 871.51) 
(list 2240.5441 871.51)))
(apply 'command (append '("pline") coords '("c")))
(setq tap7 (ssadd (entlast) tap7))
(command "_mirror" (entlast) "" "2240,900" "2240,901" "No")
(setq tap7 (ssadd (entlast) tap7))
(setq coords (list 
(list 2241.128 871.14) 
(list 2240.5441 871.14) 
(list 2240.5441 871.1503) 
(list 2240.5441 871.1606) 
(list 2240.5441 871.1708) 
(list 2240.5441 871.1811) 
(list 2240.5441 871.1914) 
(list 2240.5441 871.2017) 
(list 2240.5441 871.2119) 
(list 2240.5441 871.2222) 
(list 2240.5441 871.2325) 
(list 2240.5441 871.2428) 
(list 2240.5441 871.2531) 
(list 2240.5441 871.2633) 
(list 2240.5441 871.2736) 
(list 2240.5441 871.2839) 
(list 2240.5441 871.2942) 
(list 2240.5441 871.3044) 
(list 2240.5441 871.3147) 
(list 2240.5441 871.325) 
(list 2240.5441 871.3353) 
(list 2240.5441 871.3456) 
(list 2240.5441 871.3558) 
(list 2240.5441 871.3661) 
(list 2240.5441 871.3764) 
(list 2240.5441 871.3867) 
(list 2240.5441 871.3969) 
(list 2240.5441 871.4072) 
(list 2240.5441 871.4175) 
(list 2240.5441 871.4278) 
(list 2240.5441 871.4381) 
(list 2240.5441 871.4483) 
(list 2240.5441 871.4586) 
(list 2240.5441 871.4689) 
(list 2240.5441 871.4792) 
(list 2240.5441 871.4894) 
(list 2240.5441 871.4997) 
(list 2240.5441 871.51) 
(list 2241.128 871.51)))
(apply 'command (append '("pline") coords '("c")))
(setq tap7 (ssadd (entlast) tap7))
(command "_mirror" (entlast) "" "2240,900" "2240,901" "No")
(setq tap7 (ssadd (entlast) tap7))
(setq coords (list 
(list 2240 871.51) 
(list 2240.135 871.51) 
(list 2240.135 871.5203) 
(list 2240.135 871.5306) 
(list 2240.135 871.5408) 
(list 2240.135 871.5511) 
(list 2240.135 871.5614) 
(list 2240.135 871.5717) 
(list 2240.135 871.5819) 
(list 2240.135 871.5922) 
(list 2240.135 871.6025) 
(list 2240.135 871.6128) 
(list 2240.135 871.6231) 
(list 2240.135 871.6333) 
(list 2240.135 871.6436) 
(list 2240.135 871.6539) 
(list 2240.135 871.6642) 
(list 2240.135 871.6744) 
(list 2240.135 871.6847) 
(list 2240.135 871.695) 
(list 2240.135 871.7053) 
(list 2240.135 871.7156) 
(list 2240.135 871.7258) 
(list 2240.135 871.7361) 
(list 2240.135 871.7464) 
(list 2240.135 871.7567) 
(list 2240.135 871.7669) 
(list 2240.135 871.7772) 
(list 2240.135 871.7875) 
(list 2240.135 871.7978) 
(list 2240.135 871.8081) 
(list 2240.135 871.8183) 
(list 2240.135 871.8286) 
(list 2240.135 871.8389) 
(list 2240.135 871.8492) 
(list 2240.135 871.8594) 
(list 2240.135 871.8697) 
(list 2240.135 871.88) 
(list 2240 871.88)))
(apply 'command (append '("pline") coords '("c")))
(setq tap7 (ssadd (entlast) tap7))
(command "_mirror" (entlast) "" "2240,900" "2240,901" "No")
(setq tap7 (ssadd (entlast) tap7))
(setq coords (list 
(list 2240.5541 871.51) 
(list 2240.5441 871.51) 
(list 2240.5426 871.5203) 
(list 2240.5376 871.5306) 
(list 2240.5292 871.5408) 
(list 2240.5176 871.5511) 
(list 2240.5033 871.5614) 
(list 2240.4865 871.5717) 
(list 2240.4679 871.5819) 
(list 2240.448 871.5922) 
(list 2240.4274 871.6025) 
(list 2240.4066 871.6128) 
(list 2240.3865 871.6231) 
(list 2240.3674 871.6333) 
(list 2240.3502 871.6436) 
(list 2240.3352 871.6539) 
(list 2240.323 871.6642) 
(list 2240.3138 871.6744) 
(list 2240.3082 871.6847) 
(list 2240.3061 871.695) 
(list 2240.3077 871.7053) 
(list 2240.313 871.7156) 
(list 2240.3218 871.7258) 
(list 2240.3339 871.7361) 
(list 2240.3488 871.7464) 
(list 2240.3663 871.7567) 
(list 2240.3856 871.7669) 
(list 2240.4064 871.7772) 
(list 2240.4278 871.7875) 
(list 2240.4494 871.7978) 
(list 2240.4704 871.8081) 
(list 2240.4902 871.8183) 
(list 2240.5081 871.8286) 
(list 2240.5237 871.8389) 
(list 2240.5365 871.8492) 
(list 2240.5459 871.8594) 
(list 2240.5519 871.8697) 
(list 2240.5541 871.88) 
(list 2240.5541 871.88)))
(apply 'command (append '("pline") coords '("c")))
(setq tap7 (ssadd (entlast) tap7))
(command "_mirror" (entlast) "" "2240,900" "2240,901" "No")
(setq tap7 (ssadd (entlast) tap7))
(setq coords (list 
(list 2241.128 871.51) 
(list 2240.5541 871.51) 
(list 2240.5541 871.5203) 
(list 2240.5541 871.5306) 
(list 2240.5541 871.5408) 
(list 2240.5541 871.5511) 
(list 2240.5541 871.5614) 
(list 2240.5541 871.5717) 
(list 2240.5541 871.5819) 
(list 2240.5541 871.5922) 
(list 2240.5541 871.6025) 
(list 2240.5541 871.6128) 
(list 2240.5541 871.6231) 
(list 2240.5541 871.6333) 
(list 2240.5541 871.6436) 
(list 2240.5541 871.6539) 
(list 2240.5541 871.6642) 
(list 2240.5541 871.6744) 
(list 2240.5541 871.6847) 
(list 2240.5541 871.695) 
(list 2240.5541 871.7053) 
(list 2240.5541 871.7156) 
(list 2240.5541 871.7258) 
(list 2240.5541 871.7361) 
(list 2240.5541 871.7464) 
(list 2240.5541 871.7567) 
(list 2240.5541 871.7669) 
(list 2240.5541 871.7772) 
(list 2240.5541 871.7875) 
(list 2240.5541 871.7978) 
(list 2240.5541 871.8081) 
(list 2240.5541 871.8183) 
(list 2240.5541 871.8286) 
(list 2240.5541 871.8389) 
(list 2240.5541 871.8492) 
(list 2240.5541 871.8594) 
(list 2240.5541 871.8697) 
(list 2240.5541 871.88) 
(list 2241.128 871.88)))
(apply 'command (append '("pline") coords '("c")))
(setq tap7 (ssadd (entlast) tap7))
(command "_mirror" (entlast) "" "2240,900" "2240,901" "No")
(setq tap7 (ssadd (entlast) tap7))
(setq coords (list 
(list 2240 871.88) 
(list 2240.135 871.88) 
(list 2240.135 871.8903) 
(list 2240.135 871.9006) 
(list 2240.135 871.9108) 
(list 2240.135 871.9211) 
(list 2240.135 871.9314) 
(list 2240.135 871.9417) 
(list 2240.135 871.9519) 
(list 2240.135 871.9622) 
(list 2240.135 871.9725) 
(list 2240.135 871.9828) 
(list 2240.135 871.9931) 
(list 2240.135 872.0033) 
(list 2240.135 872.0136) 
(list 2240.135 872.0239) 
(list 2240.135 872.0342) 
(list 2240.135 872.0444) 
(list 2240.135 872.0547) 
(list 2240.135 872.065) 
(list 2240.135 872.0753) 
(list 2240.135 872.0856) 
(list 2240.135 872.0958) 
(list 2240.135 872.1061) 
(list 2240.135 872.1164) 
(list 2240.135 872.1267) 
(list 2240.135 872.1369) 
(list 2240.135 872.1472) 
(list 2240.135 872.1575) 
(list 2240.135 872.1678) 
(list 2240.135 872.1781) 
(list 2240.135 872.1883) 
(list 2240.135 872.1986) 
(list 2240.135 872.2089) 
(list 2240.135 872.2192) 
(list 2240.135 872.2294) 
(list 2240.135 872.2397) 
(list 2240.135 872.25) 
(list 2240 872.25)))
(apply 'command (append '("pline") coords '("c")))
(setq tap7 (ssadd (entlast) tap7))
(command "_mirror" (entlast) "" "2240,900" "2240,901" "No")
(setq tap7 (ssadd (entlast) tap7))
(setq coords (list 
(list 2240.564 871.88) 
(list 2240.5541 871.88) 
(list 2240.5524 871.8903) 
(list 2240.547 871.9006) 
(list 2240.5379 871.9108) 
(list 2240.5255 871.9211) 
(list 2240.51 871.9314) 
(list 2240.492 871.9417) 
(list 2240.4719 871.9519) 
(list 2240.4505 871.9622) 
(list 2240.4283 871.9725) 
(list 2240.406 871.9828) 
(list 2240.3843 871.9931) 
(list 2240.3639 872.0033) 
(list 2240.3453 872.0136) 
(list 2240.3292 872.0239) 
(list 2240.3161 872.0342) 
(list 2240.3063 872.0444) 
(list 2240.3002 872.0547) 
(list 2240.298 872.065) 
(list 2240.2998 872.0753) 
(list 2240.3055 872.0856) 
(list 2240.3149 872.0958) 
(list 2240.3279 872.1061) 
(list 2240.344 872.1164) 
(list 2240.3627 872.1267) 
(list 2240.3835 872.1369) 
(list 2240.4057 872.1472) 
(list 2240.4288 872.1575) 
(list 2240.4519 872.1678) 
(list 2240.4744 872.1781) 
(list 2240.4956 872.1883) 
(list 2240.5148 872.1986) 
(list 2240.5315 872.2089) 
(list 2240.5452 872.2192) 
(list 2240.5553 872.2294) 
(list 2240.5617 872.2397) 
(list 2240.564 872.25) 
(list 2240.564 872.25)))
(apply 'command (append '("pline") coords '("c")))
(setq tap7 (ssadd (entlast) tap7))
(command "_mirror" (entlast) "" "2240,900" "2240,901" "No")
(setq tap7 (ssadd (entlast) tap7))
(setq coords (list 
(list 2241.128 871.88) 
(list 2240.564 871.88) 
(list 2240.564 871.8903) 
(list 2240.564 871.9006) 
(list 2240.564 871.9108) 
(list 2240.564 871.9211) 
(list 2240.564 871.9314) 
(list 2240.564 871.9417) 
(list 2240.564 871.9519) 
(list 2240.564 871.9622) 
(list 2240.564 871.9725) 
(list 2240.564 871.9828) 
(list 2240.564 871.9931) 
(list 2240.564 872.0033) 
(list 2240.564 872.0136) 
(list 2240.564 872.0239) 
(list 2240.564 872.0342) 
(list 2240.564 872.0444) 
(list 2240.564 872.0547) 
(list 2240.564 872.065) 
(list 2240.564 872.0753) 
(list 2240.564 872.0856) 
(list 2240.564 872.0958) 
(list 2240.564 872.1061) 
(list 2240.564 872.1164) 
(list 2240.564 872.1267) 
(list 2240.564 872.1369) 
(list 2240.564 872.1472) 
(list 2240.564 872.1575) 
(list 2240.564 872.1678) 
(list 2240.564 872.1781) 
(list 2240.564 872.1883) 
(list 2240.564 872.1986) 
(list 2240.564 872.2089) 
(list 2240.564 872.2192) 
(list 2240.564 872.2294) 
(list 2240.564 872.2397) 
(list 2240.564 872.25) 
(list 2241.128 872.25)))
(apply 'command (append '("pline") coords '("c")))
(setq tap7 (ssadd (entlast) tap7))
(command "_mirror" (entlast) "" "2240,900" "2240,901" "No")
(setq tap7 (ssadd (entlast) tap7))
(command "_block" "blktap7" "2240,900" tap7 "")
(command "_insert" "blktap7" "2240,900" "1" "1" "0")
(command "_insert" "blktap7" "2240,900" "1" "1" "180")
(setq uc7 nil)
(setq uc7 (ssadd))
(setq coords (list 
(list 0 -0.185) 
(list 0.135 -0.185) 
(list 0.135 -0.17472) 
(list 0.135 -0.16444) 
(list 0.135 -0.15417) 
(list 0.135 -0.14389) 
(list 0.135 -0.13361) 
(list 0.135 -0.12333) 
(list 0.135 -0.11306) 
(list 0.135 -0.10278) 
(list 0.135 -0.0925) 
(list 0.135 -0.082222) 
(list 0.135 -0.071944) 
(list 0.135 -0.061667) 
(list 0.135 -0.051389) 
(list 0.135 -0.041111) 
(list 0.135 -0.030833) 
(list 0.135 -0.020556) 
(list 0.135 -0.010278) 
(list 0.135 0) 
(list 0.135 0.010278) 
(list 0.135 0.020556) 
(list 0.135 0.030833) 
(list 0.135 0.041111) 
(list 0.135 0.051389) 
(list 0.135 0.061667) 
(list 0.135 0.071944) 
(list 0.135 0.082222) 
(list 0.135 0.0925) 
(list 0.135 0.10278) 
(list 0.135 0.11306) 
(list 0.135 0.12333) 
(list 0.135 0.13361) 
(list 0.135 0.14389) 
(list 0.135 0.15417) 
(list 0.135 0.16444) 
(list 0.135 0.17472) 
(list 0.135 0.185) 
(list 0 0.185)))
(apply 'command (append '("pline") coords '("c")))
(setq uc7 (ssadd (entlast) uc7))
(setq coords (list 
(list 1.128 -0.185) 
(list 0.564 -0.185) 
(list 0.56195 -0.17472) 
(list 0.55586 -0.16444) 
(list 0.54591 -0.15417) 
(list 0.53242 -0.14389) 
(list 0.51578 -0.13361) 
(list 0.4965 -0.12333) 
(list 0.47517 -0.11306) 
(list 0.45244 -0.10278) 
(list 0.429 -0.0925) 
(list 0.40556 -0.082222) 
(list 0.38283 -0.071944) 
(list 0.3615 -0.061667) 
(list 0.34222 -0.051389) 
(list 0.32558 -0.041111) 
(list 0.31209 -0.030833) 
(list 0.30214 -0.020556) 
(list 0.29605 -0.010278) 
(list 0.294 0) 
(list 0.29605 0.010278) 
(list 0.30214 0.020556) 
(list 0.31209 0.030833) 
(list 0.32558 0.041111) 
(list 0.34222 0.051389) 
(list 0.3615 0.061667) 
(list 0.38283 0.071944) 
(list 0.40556 0.082222) 
(list 0.429 0.0925) 
(list 0.45244 0.10278) 
(list 0.47517 0.11306) 
(list 0.4965 0.12333) 
(list 0.51578 0.13361) 
(list 0.53242 0.14389) 
(list 0.54591 0.15417) 
(list 0.55586 0.16444) 
(list 0.56195 0.17472) 
(list 0.564 0.185) 
(list 1.128 0.185)))
(apply 'command (append '("pline") coords '("c")))
(setq uc7 (ssadd (entlast) uc7))
(command "_block" "blkuc7" "0,0.185" uc7 "")
(command "_insert" "blkuc7" "2240,872.62" "1" "1" "0")
(command "_insert" "blkuc7" "2240,872.25" "1" "1" "180")
(command "_insert" "blkuc7" "2240,872.99" "1" "1" "0")
(command "_insert" "blkuc7" "2240,872.62" "1" "1" "180")
(command "_insert" "blkuc7" "2240,873.36" "1" "1" "0")
(command "_insert" "blkuc7" "2240,872.99" "1" "1" "180")
(command "_insert" "blkuc7" "2240,873.73" "1" "1" "0")
(command "_insert" "blkuc7" "2240,873.36" "1" "1" "180")
(command "_insert" "blkuc7" "2240,874.1" "1" "1" "0")
(command "_insert" "blkuc7" "2240,873.73" "1" "1" "180")
(command "_insert" "blkuc7" "2240,874.47" "1" "1" "0")
(command "_insert" "blkuc7" "2240,874.1" "1" "1" "180")
(command "_insert" "blkuc7" "2240,874.84" "1" "1" "0")
(command "_insert" "blkuc7" "2240,874.47" "1" "1" "180")
(command "_insert" "blkuc7" "2240,875.21" "1" "1" "0")
(command "_insert" "blkuc7" "2240,874.84" "1" "1" "180")
(command "_insert" "blkuc7" "2240,875.58" "1" "1" "0")
(command "_insert" "blkuc7" "2240,875.21" "1" "1" "180")
(command "_insert" "blkuc7" "2240,875.95" "1" "1" "0")
(command "_insert" "blkuc7" "2240,875.58" "1" "1" "180")
(command "_insert" "blkuc7" "2240,876.32" "1" "1" "0")
(command "_insert" "blkuc7" "2240,875.95" "1" "1" "180")
(command "_insert" "blkuc7" "2240,876.69" "1" "1" "0")
(command "_insert" "blkuc7" "2240,876.32" "1" "1" "180")
(command "_insert" "blkuc7" "2240,877.06" "1" "1" "0")
(command "_insert" "blkuc7" "2240,876.69" "1" "1" "180")
(command "_insert" "blkuc7" "2240,877.43" "1" "1" "0")
(command "_insert" "blkuc7" "2240,877.06" "1" "1" "180")
(command "_insert" "blkuc7" "2240,877.8" "1" "1" "0")
(command "_insert" "blkuc7" "2240,877.43" "1" "1" "180")
(command "_insert" "blkuc7" "2240,878.17" "1" "1" "0")
(command "_insert" "blkuc7" "2240,877.8" "1" "1" "180")
(command "_insert" "blkuc7" "2240,878.54" "1" "1" "0")
(command "_insert" "blkuc7" "2240,878.17" "1" "1" "180")
(command "_insert" "blkuc7" "2240,878.91" "1" "1" "0")
(command "_insert" "blkuc7" "2240,878.54" "1" "1" "180")
(command "_insert" "blkuc7" "2240,879.28" "1" "1" "0")
(command "_insert" "blkuc7" "2240,878.91" "1" "1" "180")
(command "_insert" "blkuc7" "2240,879.65" "1" "1" "0")
(command "_insert" "blkuc7" "2240,879.28" "1" "1" "180")
(command "_insert" "blkuc7" "2240,880.02" "1" "1" "0")
(command "_insert" "blkuc7" "2240,879.65" "1" "1" "180")
(command "_insert" "blkuc7" "2240,880.39" "1" "1" "0")
(command "_insert" "blkuc7" "2240,880.02" "1" "1" "180")
(command "_insert" "blkuc7" "2240,880.76" "1" "1" "0")
(command "_insert" "blkuc7" "2240,880.39" "1" "1" "180")
(command "_insert" "blkuc7" "2240,881.13" "1" "1" "0")
(command "_insert" "blkuc7" "2240,880.76" "1" "1" "180")
(command "_insert" "blkuc7" "2240,881.5" "1" "1" "0")
(command "_insert" "blkuc7" "2240,881.13" "1" "1" "180")
(command "_insert" "blkuc7" "2240,881.87" "1" "1" "0")
(command "_insert" "blkuc7" "2240,881.5" "1" "1" "180")
(command "_insert" "blkuc7" "2240,882.24" "1" "1" "0")
(command "_insert" "blkuc7" "2240,881.87" "1" "1" "180")
(command "_insert" "blkuc7" "2240,882.61" "1" "1" "0")
(command "_insert" "blkuc7" "2240,882.24" "1" "1" "180")
(command "_insert" "blkuc7" "2240,882.98" "1" "1" "0")
(command "_insert" "blkuc7" "2240,882.61" "1" "1" "180")
(command "_insert" "blkuc7" "2240,883.35" "1" "1" "0")
(command "_insert" "blkuc7" "2240,882.98" "1" "1" "180")
(command "_insert" "blkuc7" "2240,883.72" "1" "1" "0")
(command "_insert" "blkuc7" "2240,883.35" "1" "1" "180")
(command "_insert" "blkuc7" "2240,884.09" "1" "1" "0")
(command "_insert" "blkuc7" "2240,883.72" "1" "1" "180")
(command "_insert" "blkuc7" "2240,884.46" "1" "1" "0")
(command "_insert" "blkuc7" "2240,884.09" "1" "1" "180")
(command "_insert" "blkuc7" "2240,884.83" "1" "1" "0")
(command "_insert" "blkuc7" "2240,884.46" "1" "1" "180")
(command "_insert" "blkuc7" "2240,885.2" "1" "1" "0")
(command "_insert" "blkuc7" "2240,884.83" "1" "1" "180")
(command "_insert" "blkuc7" "2240,885.57" "1" "1" "0")
(command "_insert" "blkuc7" "2240,885.2" "1" "1" "180")
(command "_insert" "blkuc7" "2240,885.94" "1" "1" "0")
(command "_insert" "blkuc7" "2240,885.57" "1" "1" "180")
(command "_insert" "blkuc7" "2240,886.31" "1" "1" "0")
(command "_insert" "blkuc7" "2240,885.94" "1" "1" "180")
(command "_insert" "blkuc7" "2240,886.68" "1" "1" "0")
(command "_insert" "blkuc7" "2240,886.31" "1" "1" "180")
(command "_insert" "blkuc7" "2240,887.05" "1" "1" "0")
(command "_insert" "blkuc7" "2240,886.68" "1" "1" "180")
(command "_insert" "blkuc7" "2240,887.42" "1" "1" "0")
(command "_insert" "blkuc7" "2240,887.05" "1" "1" "180")
(command "_insert" "blkuc7" "2240,887.79" "1" "1" "0")
(command "_insert" "blkuc7" "2240,887.42" "1" "1" "180")
(command "_insert" "blkuc7" "2240,888.16" "1" "1" "0")
(command "_insert" "blkuc7" "2240,887.79" "1" "1" "180")
(command "_insert" "blkuc7" "2240,888.53" "1" "1" "0")
(command "_insert" "blkuc7" "2240,888.16" "1" "1" "180")
(command "_insert" "blkuc7" "2240,888.9" "1" "1" "0")
(command "_insert" "blkuc7" "2240,888.53" "1" "1" "180")
(command "_insert" "blkuc7" "2240,889.27" "1" "1" "0")
(command "_insert" "blkuc7" "2240,888.9" "1" "1" "180")
(command "_insert" "blkuc7" "2240,889.64" "1" "1" "0")
(command "_insert" "blkuc7" "2240,889.27" "1" "1" "180")
(command "_insert" "blkuc7" "2240,890.01" "1" "1" "0")
(command "_insert" "blkuc7" "2240,889.64" "1" "1" "180")
(command "_insert" "blkuc7" "2240,890.38" "1" "1" "0")
(command "_insert" "blkuc7" "2240,890.01" "1" "1" "180")
(command "_insert" "blkuc7" "2240,890.75" "1" "1" "0")
(command "_insert" "blkuc7" "2240,890.38" "1" "1" "180")
(command "_insert" "blkuc7" "2240,891.12" "1" "1" "0")
(command "_insert" "blkuc7" "2240,890.75" "1" "1" "180")
(command "_insert" "blkuc7" "2240,891.49" "1" "1" "0")
(command "_insert" "blkuc7" "2240,891.12" "1" "1" "180")
(command "_insert" "blkuc7" "2240,891.86" "1" "1" "0")
(command "_insert" "blkuc7" "2240,891.49" "1" "1" "180")
(command "_insert" "blkuc7" "2240,892.23" "1" "1" "0")
(command "_insert" "blkuc7" "2240,891.86" "1" "1" "180")
(command "_insert" "blkuc7" "2240,892.6" "1" "1" "0")
(command "_insert" "blkuc7" "2240,892.23" "1" "1" "180")
(command "_insert" "blkuc7" "2240,892.97" "1" "1" "0")
(command "_insert" "blkuc7" "2240,892.6" "1" "1" "180")
(command "_insert" "blkuc7" "2240,893.34" "1" "1" "0")
(command "_insert" "blkuc7" "2240,892.97" "1" "1" "180")
(command "_insert" "blkuc7" "2240,893.71" "1" "1" "0")
(command "_insert" "blkuc7" "2240,893.34" "1" "1" "180")
(command "_insert" "blkuc7" "2240,894.08" "1" "1" "0")
(command "_insert" "blkuc7" "2240,893.71" "1" "1" "180")
(command "_insert" "blkuc7" "2240,894.45" "1" "1" "0")
(command "_insert" "blkuc7" "2240,894.08" "1" "1" "180")
(command "_insert" "blkuc7" "2240,894.82" "1" "1" "0")
(command "_insert" "blkuc7" "2240,894.45" "1" "1" "180")
(command "_insert" "blkuc7" "2240,895.19" "1" "1" "0")
(command "_insert" "blkuc7" "2240,894.82" "1" "1" "180")
(command "_insert" "blkuc7" "2240,895.56" "1" "1" "0")
(command "_insert" "blkuc7" "2240,895.19" "1" "1" "180")
(command "_insert" "blkuc7" "2240,895.93" "1" "1" "0")
(command "_insert" "blkuc7" "2240,895.56" "1" "1" "180")
(command "_insert" "blkuc7" "2240,896.3" "1" "1" "0")
(command "_insert" "blkuc7" "2240,895.93" "1" "1" "180")
(command "_insert" "blkuc7" "2240,896.67" "1" "1" "0")
(command "_insert" "blkuc7" "2240,896.3" "1" "1" "180")
(command "_insert" "blkuc7" "2240,897.04" "1" "1" "0")
(command "_insert" "blkuc7" "2240,896.67" "1" "1" "180")
(command "_insert" "blkuc7" "2240,897.41" "1" "1" "0")
(command "_insert" "blkuc7" "2240,897.04" "1" "1" "180")
(command "_insert" "blkuc7" "2240,897.78" "1" "1" "0")
(command "_insert" "blkuc7" "2240,897.41" "1" "1" "180")
(command "_insert" "blkuc7" "2240,898.15" "1" "1" "0")
(command "_insert" "blkuc7" "2240,897.78" "1" "1" "180")
(command "_insert" "blkuc7" "2240,898.52" "1" "1" "0")
(command "_insert" "blkuc7" "2240,898.15" "1" "1" "180")
(command "_insert" "blkuc7" "2240,898.89" "1" "1" "0")
(command "_insert" "blkuc7" "2240,898.52" "1" "1" "180")
(command "_insert" "blkuc7" "2240,899.26" "1" "1" "0")
(command "_insert" "blkuc7" "2240,898.89" "1" "1" "180")
(command "_insert" "blkuc7" "2240,899.63" "1" "1" "0")
(command "_insert" "blkuc7" "2240,899.26" "1" "1" "180")
(command "_insert" "blkuc7" "2240,900" "1" "1" "0")
(command "_insert" "blkuc7" "2240,899.63" "1" "1" "180")
(command "_insert" "blkuc7" "2240,900.37" "1" "1" "0")
(command "_insert" "blkuc7" "2240,900" "1" "1" "180")
(command "_insert" "blkuc7" "2240,900.74" "1" "1" "0")
(command "_insert" "blkuc7" "2240,900.37" "1" "1" "180")
(command "_insert" "blkuc7" "2240,901.11" "1" "1" "0")
(command "_insert" "blkuc7" "2240,900.74" "1" "1" "180")
(command "_insert" "blkuc7" "2240,901.48" "1" "1" "0")
(command "_insert" "blkuc7" "2240,901.11" "1" "1" "180")
(command "_insert" "blkuc7" "2240,901.85" "1" "1" "0")
(command "_insert" "blkuc7" "2240,901.48" "1" "1" "180")
(command "_insert" "blkuc7" "2240,902.22" "1" "1" "0")
(command "_insert" "blkuc7" "2240,901.85" "1" "1" "180")
(command "_insert" "blkuc7" "2240,902.59" "1" "1" "0")
(command "_insert" "blkuc7" "2240,902.22" "1" "1" "180")
(command "_insert" "blkuc7" "2240,902.96" "1" "1" "0")
(command "_insert" "blkuc7" "2240,902.59" "1" "1" "180")
(command "_insert" "blkuc7" "2240,903.33" "1" "1" "0")
(command "_insert" "blkuc7" "2240,902.96" "1" "1" "180")
(command "_insert" "blkuc7" "2240,903.7" "1" "1" "0")
(command "_insert" "blkuc7" "2240,903.33" "1" "1" "180")
(command "_insert" "blkuc7" "2240,904.07" "1" "1" "0")
(command "_insert" "blkuc7" "2240,903.7" "1" "1" "180")
(command "_insert" "blkuc7" "2240,904.44" "1" "1" "0")
(command "_insert" "blkuc7" "2240,904.07" "1" "1" "180")
(command "_insert" "blkuc7" "2240,904.81" "1" "1" "0")
(command "_insert" "blkuc7" "2240,904.44" "1" "1" "180")
(command "_insert" "blkuc7" "2240,905.18" "1" "1" "0")
(command "_insert" "blkuc7" "2240,904.81" "1" "1" "180")
(command "_insert" "blkuc7" "2240,905.55" "1" "1" "0")
(command "_insert" "blkuc7" "2240,905.18" "1" "1" "180")
(command "_insert" "blkuc7" "2240,905.92" "1" "1" "0")
(command "_insert" "blkuc7" "2240,905.55" "1" "1" "180")
(command "_insert" "blkuc7" "2240,906.29" "1" "1" "0")
(command "_insert" "blkuc7" "2240,905.92" "1" "1" "180")
(command "_insert" "blkuc7" "2240,906.66" "1" "1" "0")
(command "_insert" "blkuc7" "2240,906.29" "1" "1" "180")
(command "_insert" "blkuc7" "2240,907.03" "1" "1" "0")
(command "_insert" "blkuc7" "2240,906.66" "1" "1" "180")
(command "_insert" "blkuc7" "2240,907.4" "1" "1" "0")
(command "_insert" "blkuc7" "2240,907.03" "1" "1" "180")
(command "_insert" "blkuc7" "2240,907.77" "1" "1" "0")
(command "_insert" "blkuc7" "2240,907.4" "1" "1" "180")
(command "_insert" "blkuc7" "2240,908.14" "1" "1" "0")
(command "_insert" "blkuc7" "2240,907.77" "1" "1" "180")
(command "_insert" "blkuc7" "2240,908.51" "1" "1" "0")
(command "_insert" "blkuc7" "2240,908.14" "1" "1" "180")
(command "_insert" "blkuc7" "2240,908.88" "1" "1" "0")
(command "_insert" "blkuc7" "2240,908.51" "1" "1" "180")
(command "_insert" "blkuc7" "2240,909.25" "1" "1" "0")
(command "_insert" "blkuc7" "2240,908.88" "1" "1" "180")
(command "_insert" "blkuc7" "2240,909.62" "1" "1" "0")
(command "_insert" "blkuc7" "2240,909.25" "1" "1" "180")
(command "_insert" "blkuc7" "2240,909.99" "1" "1" "0")
(command "_insert" "blkuc7" "2240,909.62" "1" "1" "180")
(command "_insert" "blkuc7" "2240,910.36" "1" "1" "0")
(command "_insert" "blkuc7" "2240,909.99" "1" "1" "180")
(command "_insert" "blkuc7" "2240,910.73" "1" "1" "0")
(command "_insert" "blkuc7" "2240,910.36" "1" "1" "180")
(command "_insert" "blkuc7" "2240,911.1" "1" "1" "0")
(command "_insert" "blkuc7" "2240,910.73" "1" "1" "180")
(command "_insert" "blkuc7" "2240,911.47" "1" "1" "0")
(command "_insert" "blkuc7" "2240,911.1" "1" "1" "180")
(command "_insert" "blkuc7" "2240,911.84" "1" "1" "0")
(command "_insert" "blkuc7" "2240,911.47" "1" "1" "180")
(command "_insert" "blkuc7" "2240,912.21" "1" "1" "0")
(command "_insert" "blkuc7" "2240,911.84" "1" "1" "180")
(command "_insert" "blkuc7" "2240,912.58" "1" "1" "0")
(command "_insert" "blkuc7" "2240,912.21" "1" "1" "180")
(command "_insert" "blkuc7" "2240,912.95" "1" "1" "0")
(command "_insert" "blkuc7" "2240,912.58" "1" "1" "180")
(command "_insert" "blkuc7" "2240,913.32" "1" "1" "0")
(command "_insert" "blkuc7" "2240,912.95" "1" "1" "180")
(command "_insert" "blkuc7" "2240,913.69" "1" "1" "0")
(command "_insert" "blkuc7" "2240,913.32" "1" "1" "180")
(command "_insert" "blkuc7" "2240,914.06" "1" "1" "0")
(command "_insert" "blkuc7" "2240,913.69" "1" "1" "180")
(command "_insert" "blkuc7" "2240,914.43" "1" "1" "0")
(command "_insert" "blkuc7" "2240,914.06" "1" "1" "180")
(command "_insert" "blkuc7" "2240,914.8" "1" "1" "0")
(command "_insert" "blkuc7" "2240,914.43" "1" "1" "180")
(command "_insert" "blkuc7" "2240,915.17" "1" "1" "0")
(command "_insert" "blkuc7" "2240,914.8" "1" "1" "180")
(command "_insert" "blkuc7" "2240,915.54" "1" "1" "0")
(command "_insert" "blkuc7" "2240,915.17" "1" "1" "180")
(command "_insert" "blkuc7" "2240,915.91" "1" "1" "0")
(command "_insert" "blkuc7" "2240,915.54" "1" "1" "180")
(command "_insert" "blkuc7" "2240,916.28" "1" "1" "0")
(command "_insert" "blkuc7" "2240,915.91" "1" "1" "180")
(command "_insert" "blkuc7" "2240,916.65" "1" "1" "0")
(command "_insert" "blkuc7" "2240,916.28" "1" "1" "180")
(command "_insert" "blkuc7" "2240,917.02" "1" "1" "0")
(command "_insert" "blkuc7" "2240,916.65" "1" "1" "180")
(command "_insert" "blkuc7" "2240,917.39" "1" "1" "0")
(command "_insert" "blkuc7" "2240,917.02" "1" "1" "180")
(command "_insert" "blkuc7" "2240,917.76" "1" "1" "0")
(command "_insert" "blkuc7" "2240,917.39" "1" "1" "180")
(command "_insert" "blkuc7" "2240,918.13" "1" "1" "0")
(command "_insert" "blkuc7" "2240,917.76" "1" "1" "180")
(command "_insert" "blkuc7" "2240,918.5" "1" "1" "0")
(command "_insert" "blkuc7" "2240,918.13" "1" "1" "180")
(command "_insert" "blkuc7" "2240,918.87" "1" "1" "0")
(command "_insert" "blkuc7" "2240,918.5" "1" "1" "180")
(command "_insert" "blkuc7" "2240,919.24" "1" "1" "0")
(command "_insert" "blkuc7" "2240,918.87" "1" "1" "180")
(command "_insert" "blkuc7" "2240,919.61" "1" "1" "0")
(command "_insert" "blkuc7" "2240,919.24" "1" "1" "180")
(command "_insert" "blkuc7" "2240,919.98" "1" "1" "0")
(command "_insert" "blkuc7" "2240,919.61" "1" "1" "180")
(command "_insert" "blkuc7" "2240,920.35" "1" "1" "0")
(command "_insert" "blkuc7" "2240,919.98" "1" "1" "180")
(command "_insert" "blkuc7" "2240,920.72" "1" "1" "0")
(command "_insert" "blkuc7" "2240,920.35" "1" "1" "180")
(command "_insert" "blkuc7" "2240,921.09" "1" "1" "0")
(command "_insert" "blkuc7" "2240,920.72" "1" "1" "180")
(command "_insert" "blkuc7" "2240,921.46" "1" "1" "0")
(command "_insert" "blkuc7" "2240,921.09" "1" "1" "180")
(command "_insert" "blkuc7" "2240,921.83" "1" "1" "0")
(command "_insert" "blkuc7" "2240,921.46" "1" "1" "180")
(command "_insert" "blkuc7" "2240,922.2" "1" "1" "0")
(command "_insert" "blkuc7" "2240,921.83" "1" "1" "180")
(command "_insert" "blkuc7" "2240,922.57" "1" "1" "0")
(command "_insert" "blkuc7" "2240,922.2" "1" "1" "180")
(command "_insert" "blkuc7" "2240,922.94" "1" "1" "0")
(command "_insert" "blkuc7" "2240,922.57" "1" "1" "180")
(command "_insert" "blkuc7" "2240,923.31" "1" "1" "0")
(command "_insert" "blkuc7" "2240,922.94" "1" "1" "180")
(command "_insert" "blkuc7" "2240,923.68" "1" "1" "0")
(command "_insert" "blkuc7" "2240,923.31" "1" "1" "180")
(command "_insert" "blkuc7" "2240,924.05" "1" "1" "0")
(command "_insert" "blkuc7" "2240,923.68" "1" "1" "180")
(command "_insert" "blkuc7" "2240,924.42" "1" "1" "0")
(command "_insert" "blkuc7" "2240,924.05" "1" "1" "180")
(command "_insert" "blkuc7" "2240,924.79" "1" "1" "0")
(command "_insert" "blkuc7" "2240,924.42" "1" "1" "180")
(command "_insert" "blkuc7" "2240,925.16" "1" "1" "0")
(command "_insert" "blkuc7" "2240,924.79" "1" "1" "180")
(command "_insert" "blkuc7" "2240,925.53" "1" "1" "0")
(command "_insert" "blkuc7" "2240,925.16" "1" "1" "180")
(command "_insert" "blkuc7" "2240,925.9" "1" "1" "0")
(command "_insert" "blkuc7" "2240,925.53" "1" "1" "180")
(command "_insert" "blkuc7" "2240,926.27" "1" "1" "0")
(command "_insert" "blkuc7" "2240,925.9" "1" "1" "180")
(command "_insert" "blkuc7" "2240,926.64" "1" "1" "0")
(command "_insert" "blkuc7" "2240,926.27" "1" "1" "180")
(command "_insert" "blkuc7" "2240,927.01" "1" "1" "0")
(command "_insert" "blkuc7" "2240,926.64" "1" "1" "180")
(command "_insert" "blkuc7" "2240,927.38" "1" "1" "0")
(command "_insert" "blkuc7" "2240,927.01" "1" "1" "180")
(command "_insert" "blkuc7" "2240,927.75" "1" "1" "0")
(command "_insert" "blkuc7" "2240,927.38" "1" "1" "180")
(command "_layer" "set" "phccover" "")
(command "_rectangle" "2238.872,933.3" "2241.128,866.7")
(command "_layer" "set" "nitride" "")
(setq phc7 currobj)
(command "_layer" "set" "cover" "")
(command "_rectangle" "2238.872,836.7" "2241.128,963.3")
(command "_layer" "set" "nitride" "")
(command "_layer" "set" "text" "")
(command "_circle" "2237.922,846.7" "0.075")
(command "_circle" "2237.547,846.7" "0.15")
(command "_circle" "2237.172,846.7" "0.075")
(command "_circle" "2236.797,846.7" "0.15")
(command "_circle" "2237.922,848.7" "0.075")
(command "_circle" "2237.547,848.7" "0.075")
(command "_circle" "2237.172,848.7" "0.15")
(command "_circle" "2236.797,848.7" "0.15")
(command "_circle" "2237.922,850.7" "0.075")
(command "_circle" "2237.547,850.7" "0.15")
(command "_circle" "2237.172,850.7" "0.15")
(command "_circle" "2236.797,850.7" "0.15")
(command "_circle" "2237.922,852.7" "0.075")
(command "_circle" "2237.547,852.7" "0.075")
(command "_circle" "2237.172,852.7" "0.075")
(command "_circle" "2236.797,852.7" "0.075")
(command "_circle" "2236.422,852.7" "0.15")
(command "_circle" "2237.922,854.7" "0.075")
(command "_circle" "2237.547,854.7" "0.15")
(command "_circle" "2237.172,854.7" "0.075")
(command "_circle" "2236.797,854.7" "0.075")
(command "_circle" "2236.422,854.7" "0.15")
(command "_circle" "2237.922,856.7" "0.075")
(command "_circle" "2237.547,856.7" "0.075")
(command "_circle" "2237.172,856.7" "0.15")
(command "_circle" "2236.797,856.7" "0.075")
(command "_circle" "2236.422,856.7" "0.15")
(command "_circle" "2237.922,858.7" "0.075")
(command "_circle" "2237.547,858.7" "0.15")
(command "_circle" "2237.172,858.7" "0.15")
(command "_circle" "2236.797,858.7" "0.075")
(command "_circle" "2236.422,858.7" "0.15")
(command "_circle" "2237.922,860.7" "0.075")
(command "_circle" "2237.547,860.7" "0.075")
(command "_circle" "2237.172,860.7" "0.075")
(command "_circle" "2236.797,860.7" "0.15")
(command "_circle" "2236.422,860.7" "0.15")
(command "_circle" "2237.922,862.7" "0.075")
(command "_circle" "2237.547,862.7" "0.15")
(command "_circle" "2237.172,862.7" "0.075")
(command "_circle" "2236.797,862.7" "0.15")
(command "_circle" "2236.422,862.7" "0.15")
(command "_circle" "2237.922,864.7" "0.075")
(command "_circle" "2237.547,864.7" "0.075")
(command "_circle" "2237.172,864.7" "0.15")
(command "_circle" "2236.797,864.7" "0.15")
(command "_circle" "2236.422,864.7" "0.15")
(command "_circle" "2237.922,866.7" "0.075")
(command "_circle" "2237.547,866.7" "0.15")
(command "_circle" "2237.172,866.7" "0.15")
(command "_circle" "2236.797,866.7" "0.15")
(command "_circle" "2236.422,866.7" "0.15")
(command "_circle" "2237.922,868.7" "0.075")
(command "_circle" "2237.547,868.7" "0.075")
(command "_circle" "2237.172,868.7" "0.075")
(command "_circle" "2236.797,868.7" "0.075")
(command "_circle" "2236.422,868.7" "0.075")
(command "_circle" "2236.047,868.7" "0.15")
(command "_circle" "2237.922,870.7" "0.075")
(command "_circle" "2237.547,870.7" "0.15")
(command "_circle" "2237.172,870.7" "0.075")
(command "_circle" "2236.797,870.7" "0.075")
(command "_circle" "2236.422,870.7" "0.075")
(command "_circle" "2236.047,870.7" "0.15")
(command "_circle" "2237.922,872.7" "0.075")
(command "_circle" "2237.547,872.7" "0.075")
(command "_circle" "2237.172,872.7" "0.15")
(command "_circle" "2236.797,872.7" "0.075")
(command "_circle" "2236.422,872.7" "0.075")
(command "_circle" "2236.047,872.7" "0.15")
(command "_circle" "2237.922,874.7" "0.075")
(command "_circle" "2237.547,874.7" "0.15")
(command "_circle" "2237.172,874.7" "0.15")
(command "_circle" "2236.797,874.7" "0.075")
(command "_circle" "2236.422,874.7" "0.075")
(command "_circle" "2236.047,874.7" "0.15")
(command "_circle" "2237.922,876.7" "0.075")
(command "_circle" "2237.547,876.7" "0.075")
(command "_circle" "2237.172,876.7" "0.075")
(command "_circle" "2236.797,876.7" "0.15")
(command "_circle" "2236.422,876.7" "0.075")
(command "_circle" "2236.047,876.7" "0.15")
(command "_circle" "2237.922,878.7" "0.075")
(command "_circle" "2237.547,878.7" "0.15")
(command "_circle" "2237.172,878.7" "0.075")
(command "_circle" "2236.797,878.7" "0.15")
(command "_circle" "2236.422,878.7" "0.075")
(command "_circle" "2236.047,878.7" "0.15")
(command "_circle" "2237.922,880.7" "0.075")
(command "_circle" "2237.547,880.7" "0.075")
(command "_circle" "2237.172,880.7" "0.15")
(command "_circle" "2236.797,880.7" "0.15")
(command "_circle" "2236.422,880.7" "0.075")
(command "_circle" "2236.047,880.7" "0.15")
(command "_circle" "2237.922,882.7" "0.075")
(command "_circle" "2237.547,882.7" "0.15")
(command "_circle" "2237.172,882.7" "0.15")
(command "_circle" "2236.797,882.7" "0.15")
(command "_circle" "2236.422,882.7" "0.075")
(command "_circle" "2236.047,882.7" "0.15")
(command "_circle" "2237.922,884.7" "0.075")
(command "_circle" "2237.547,884.7" "0.075")
(command "_circle" "2237.172,884.7" "0.075")
(command "_circle" "2236.797,884.7" "0.075")
(command "_circle" "2236.422,884.7" "0.15")
(command "_circle" "2236.047,884.7" "0.15")
(command "_circle" "2237.922,886.7" "0.075")
(command "_circle" "2237.547,886.7" "0.15")
(command "_circle" "2237.172,886.7" "0.075")
(command "_circle" "2236.797,886.7" "0.075")
(command "_circle" "2236.422,886.7" "0.15")
(command "_circle" "2236.047,886.7" "0.15")
(command "_circle" "2237.922,888.7" "0.075")
(command "_circle" "2237.547,888.7" "0.075")
(command "_circle" "2237.172,888.7" "0.15")
(command "_circle" "2236.797,888.7" "0.075")
(command "_circle" "2236.422,888.7" "0.15")
(command "_circle" "2236.047,888.7" "0.15")
(command "_circle" "2237.922,890.7" "0.075")
(command "_circle" "2237.547,890.7" "0.15")
(command "_circle" "2237.172,890.7" "0.15")
(command "_circle" "2236.797,890.7" "0.075")
(command "_circle" "2236.422,890.7" "0.15")
(command "_circle" "2236.047,890.7" "0.15")
(command "_circle" "2237.922,892.7" "0.075")
(command "_circle" "2237.547,892.7" "0.075")
(command "_circle" "2237.172,892.7" "0.075")
(command "_circle" "2236.797,892.7" "0.15")
(command "_circle" "2236.422,892.7" "0.15")
(command "_circle" "2236.047,892.7" "0.15")
(command "_circle" "2237.922,894.7" "0.075")
(command "_circle" "2237.547,894.7" "0.15")
(command "_circle" "2237.172,894.7" "0.075")
(command "_circle" "2236.797,894.7" "0.15")
(command "_circle" "2236.422,894.7" "0.15")
(command "_circle" "2236.047,894.7" "0.15")
(command "_circle" "2237.922,896.7" "0.075")
(command "_circle" "2237.547,896.7" "0.075")
(command "_circle" "2237.172,896.7" "0.15")
(command "_circle" "2236.797,896.7" "0.15")
(command "_circle" "2236.422,896.7" "0.15")
(command "_circle" "2236.047,896.7" "0.15")
(command "_circle" "2237.922,898.7" "0.075")
(command "_circle" "2237.547,898.7" "0.15")
(command "_circle" "2237.172,898.7" "0.15")
(command "_circle" "2236.797,898.7" "0.15")
(command "_circle" "2236.422,898.7" "0.15")
(command "_circle" "2236.047,898.7" "0.15")
(command "_circle" "2237.922,900.7" "0.075")
(command "_circle" "2237.547,900.7" "0.075")
(command "_circle" "2237.172,900.7" "0.075")
(command "_circle" "2236.797,900.7" "0.075")
(command "_circle" "2236.422,900.7" "0.075")
(command "_circle" "2236.047,900.7" "0.075")
(command "_circle" "2235.672,900.7" "0.15")
(command "_circle" "2237.922,902.7" "0.075")
(command "_circle" "2237.547,902.7" "0.15")
(command "_circle" "2237.172,902.7" "0.075")
(command "_circle" "2236.797,902.7" "0.075")
(command "_circle" "2236.422,902.7" "0.075")
(command "_circle" "2236.047,902.7" "0.075")
(command "_circle" "2235.672,902.7" "0.15")
(command "_circle" "2237.922,904.7" "0.075")
(command "_circle" "2237.547,904.7" "0.075")
(command "_circle" "2237.172,904.7" "0.15")
(command "_circle" "2236.797,904.7" "0.075")
(command "_circle" "2236.422,904.7" "0.075")
(command "_circle" "2236.047,904.7" "0.075")
(command "_circle" "2235.672,904.7" "0.15")
(command "_circle" "2237.922,906.7" "0.075")
(command "_circle" "2237.547,906.7" "0.15")
(command "_circle" "2237.172,906.7" "0.15")
(command "_circle" "2236.797,906.7" "0.075")
(command "_circle" "2236.422,906.7" "0.075")
(command "_circle" "2236.047,906.7" "0.075")
(command "_circle" "2235.672,906.7" "0.15")
(command "_circle" "2237.922,908.7" "0.075")
(command "_circle" "2237.547,908.7" "0.075")
(command "_circle" "2237.172,908.7" "0.075")
(command "_circle" "2236.797,908.7" "0.15")
(command "_circle" "2236.422,908.7" "0.075")
(command "_circle" "2236.047,908.7" "0.075")
(command "_circle" "2235.672,908.7" "0.15")
(command "_circle" "2237.922,910.7" "0.075")
(command "_circle" "2237.547,910.7" "0.15")
(command "_circle" "2237.172,910.7" "0.075")
(command "_circle" "2236.797,910.7" "0.15")
(command "_circle" "2236.422,910.7" "0.075")
(command "_circle" "2236.047,910.7" "0.075")
(command "_circle" "2235.672,910.7" "0.15")
(command "_circle" "2237.922,912.7" "0.075")
(command "_circle" "2237.547,912.7" "0.075")
(command "_circle" "2237.172,912.7" "0.15")
(command "_circle" "2236.797,912.7" "0.15")
(command "_circle" "2236.422,912.7" "0.075")
(command "_circle" "2236.047,912.7" "0.075")
(command "_circle" "2235.672,912.7" "0.15")
(command "_circle" "2237.922,914.7" "0.075")
(command "_circle" "2237.547,914.7" "0.15")
(command "_circle" "2237.172,914.7" "0.15")
(command "_circle" "2236.797,914.7" "0.15")
(command "_circle" "2236.422,914.7" "0.075")
(command "_circle" "2236.047,914.7" "0.075")
(command "_circle" "2235.672,914.7" "0.15")
(command "_circle" "2237.922,916.7" "0.075")
(command "_circle" "2237.547,916.7" "0.075")
(command "_circle" "2237.172,916.7" "0.075")
(command "_circle" "2236.797,916.7" "0.075")
(command "_circle" "2236.422,916.7" "0.15")
(command "_circle" "2236.047,916.7" "0.075")
(command "_circle" "2235.672,916.7" "0.15")
(command "_circle" "2237.922,918.7" "0.075")
(command "_circle" "2237.547,918.7" "0.15")
(command "_circle" "2237.172,918.7" "0.075")
(command "_circle" "2236.797,918.7" "0.075")
(command "_circle" "2236.422,918.7" "0.15")
(command "_circle" "2236.047,918.7" "0.075")
(command "_circle" "2235.672,918.7" "0.15")
(command "_circle" "2237.922,920.7" "0.075")
(command "_circle" "2237.547,920.7" "0.075")
(command "_circle" "2237.172,920.7" "0.15")
(command "_circle" "2236.797,920.7" "0.075")
(command "_circle" "2236.422,920.7" "0.15")
(command "_circle" "2236.047,920.7" "0.075")
(command "_circle" "2235.672,920.7" "0.15")
(command "_circle" "2237.922,922.7" "0.075")
(command "_circle" "2237.547,922.7" "0.15")
(command "_circle" "2237.172,922.7" "0.15")
(command "_circle" "2236.797,922.7" "0.075")
(command "_circle" "2236.422,922.7" "0.15")
(command "_circle" "2236.047,922.7" "0.075")
(command "_circle" "2235.672,922.7" "0.15")
(command "_circle" "2237.922,924.7" "0.075")
(command "_circle" "2237.547,924.7" "0.075")
(command "_circle" "2237.172,924.7" "0.075")
(command "_circle" "2236.797,924.7" "0.15")
(command "_circle" "2236.422,924.7" "0.15")
(command "_circle" "2236.047,924.7" "0.075")
(command "_circle" "2235.672,924.7" "0.15")
(command "_circle" "2237.922,926.7" "0.075")
(command "_circle" "2237.547,926.7" "0.15")
(command "_circle" "2237.172,926.7" "0.075")
(command "_circle" "2236.797,926.7" "0.15")
(command "_circle" "2236.422,926.7" "0.15")
(command "_circle" "2236.047,926.7" "0.075")
(command "_circle" "2235.672,926.7" "0.15")
(command "_circle" "2237.922,928.7" "0.075")
(command "_circle" "2237.547,928.7" "0.075")
(command "_circle" "2237.172,928.7" "0.15")
(command "_circle" "2236.797,928.7" "0.15")
(command "_circle" "2236.422,928.7" "0.15")
(command "_circle" "2236.047,928.7" "0.075")
(command "_circle" "2235.672,928.7" "0.15")
(command "_circle" "2237.922,930.7" "0.075")
(command "_circle" "2237.547,930.7" "0.15")
(command "_circle" "2237.172,930.7" "0.15")
(command "_circle" "2236.797,930.7" "0.15")
(command "_circle" "2236.422,930.7" "0.15")
(command "_circle" "2236.047,930.7" "0.075")
(command "_circle" "2235.672,930.7" "0.15")
(command "_circle" "2237.922,932.7" "0.075")
(command "_circle" "2237.547,932.7" "0.075")
(command "_circle" "2237.172,932.7" "0.075")
(command "_circle" "2236.797,932.7" "0.075")
(command "_circle" "2236.422,932.7" "0.075")
(command "_circle" "2236.047,932.7" "0.15")
(command "_circle" "2235.672,932.7" "0.15")
(command "_circle" "2237.922,934.7" "0.075")
(command "_circle" "2237.547,934.7" "0.15")
(command "_circle" "2237.172,934.7" "0.075")
(command "_circle" "2236.797,934.7" "0.075")
(command "_circle" "2236.422,934.7" "0.075")
(command "_circle" "2236.047,934.7" "0.15")
(command "_circle" "2235.672,934.7" "0.15")
(command "_circle" "2237.922,936.7" "0.075")
(command "_circle" "2237.547,936.7" "0.075")
(command "_circle" "2237.172,936.7" "0.15")
(command "_circle" "2236.797,936.7" "0.075")
(command "_circle" "2236.422,936.7" "0.075")
(command "_circle" "2236.047,936.7" "0.15")
(command "_circle" "2235.672,936.7" "0.15")
(command "_circle" "2237.922,938.7" "0.075")
(command "_circle" "2237.547,938.7" "0.15")
(command "_circle" "2237.172,938.7" "0.15")
(command "_circle" "2236.797,938.7" "0.075")
(command "_circle" "2236.422,938.7" "0.075")
(command "_circle" "2236.047,938.7" "0.15")
(command "_circle" "2235.672,938.7" "0.15")
(command "_circle" "2237.922,940.7" "0.075")
(command "_circle" "2237.547,940.7" "0.075")
(command "_circle" "2237.172,940.7" "0.075")
(command "_circle" "2236.797,940.7" "0.15")
(command "_circle" "2236.422,940.7" "0.075")
(command "_circle" "2236.047,940.7" "0.15")
(command "_circle" "2235.672,940.7" "0.15")
(command "_circle" "2237.922,942.7" "0.075")
(command "_circle" "2237.547,942.7" "0.15")
(command "_circle" "2237.172,942.7" "0.075")
(command "_circle" "2236.797,942.7" "0.15")
(command "_circle" "2236.422,942.7" "0.075")
(command "_circle" "2236.047,942.7" "0.15")
(command "_circle" "2235.672,942.7" "0.15")
(command "_circle" "2237.922,944.7" "0.075")
(command "_circle" "2237.547,944.7" "0.075")
(command "_circle" "2237.172,944.7" "0.15")
(command "_circle" "2236.797,944.7" "0.15")
(command "_circle" "2236.422,944.7" "0.075")
(command "_circle" "2236.047,944.7" "0.15")
(command "_circle" "2235.672,944.7" "0.15")
(command "_circle" "2237.922,946.7" "0.075")
(command "_circle" "2237.547,946.7" "0.15")
(command "_circle" "2237.172,946.7" "0.15")
(command "_circle" "2236.797,946.7" "0.15")
(command "_circle" "2236.422,946.7" "0.075")
(command "_circle" "2236.047,946.7" "0.15")
(command "_circle" "2235.672,946.7" "0.15")
(command "_circle" "2237.922,948.7" "0.075")
(command "_circle" "2237.547,948.7" "0.075")
(command "_circle" "2237.172,948.7" "0.075")
(command "_circle" "2236.797,948.7" "0.075")
(command "_circle" "2236.422,948.7" "0.15")
(command "_circle" "2236.047,948.7" "0.15")
(command "_circle" "2235.672,948.7" "0.15")
(command "_circle" "2237.922,950.7" "0.075")
(command "_circle" "2237.547,950.7" "0.15")
(command "_circle" "2237.172,950.7" "0.075")
(command "_circle" "2236.797,950.7" "0.075")
(command "_circle" "2236.422,950.7" "0.15")
(command "_circle" "2236.047,950.7" "0.15")
(command "_circle" "2235.672,950.7" "0.15")
(command "_circle" "2237.922,952.7" "0.075")
(command "_circle" "2237.547,952.7" "0.075")
(command "_circle" "2237.172,952.7" "0.15")
(command "_circle" "2236.797,952.7" "0.075")
(command "_circle" "2236.422,952.7" "0.15")
(command "_circle" "2236.047,952.7" "0.15")
(command "_circle" "2235.672,952.7" "0.15")
(command "_circle" "2237.922,954.7" "0.075")
(command "_circle" "2237.547,954.7" "0.15")
(command "_circle" "2237.172,954.7" "0.15")
(command "_circle" "2236.797,954.7" "0.075")
(command "_circle" "2236.422,954.7" "0.15")
(command "_circle" "2236.047,954.7" "0.15")
(command "_circle" "2235.672,954.7" "0.15")
(command "_circle" "2237.922,956.7" "0.075")
(command "_circle" "2237.547,956.7" "0.075")
(command "_circle" "2237.172,956.7" "0.075")
(command "_circle" "2236.797,956.7" "0.15")
(command "_circle" "2236.422,956.7" "0.15")
(command "_circle" "2236.047,956.7" "0.15")
(command "_circle" "2235.672,956.7" "0.15")
(command "_circle" "2237.922,958.7" "0.075")
(command "_circle" "2237.547,958.7" "0.15")
(command "_circle" "2237.172,958.7" "0.075")
(command "_circle" "2236.797,958.7" "0.15")
(command "_circle" "2236.422,958.7" "0.15")
(command "_circle" "2236.047,958.7" "0.15")
(command "_circle" "2235.672,958.7" "0.15")
(command "_circle" "2237.922,960.7" "0.075")
(command "_circle" "2237.547,960.7" "0.075")
(command "_circle" "2237.172,960.7" "0.15")
(command "_circle" "2236.797,960.7" "0.15")
(command "_circle" "2236.422,960.7" "0.15")
(command "_circle" "2236.047,960.7" "0.15")
(command "_circle" "2235.672,960.7" "0.15")
(command "_circle" "2237.922,962.7" "0.075")
(command "_circle" "2237.547,962.7" "0.15")
(command "_circle" "2237.172,962.7" "0.15")
(command "_circle" "2236.797,962.7" "0.15")
(command "_circle" "2236.422,962.7" "0.15")
(command "_circle" "2236.047,962.7" "0.15")
(command "_circle" "2235.672,962.7" "0.15")
(command "_layer" "set" "nitride" "")
(command "_layer" "set" "text" "")
(command-s "_text" "2226.872,963.3" "2" "-90" "a = 370 nm" )
(sssetfirst nil (ssget "_L"))
(if (not (numberp (vl-string-search "Mac" (getvar "platform")))) (c:txtexp))
(command "_layer" "set" "nitride" "")
(command "_layer" "set" "text" "")
(command-s "_text" "2223.872,963.3" "2" "-90" "gap = 270 nm" )
(sssetfirst nil (ssget "_L"))
(if (not (numberp (vl-string-search "Mac" (getvar "platform")))) (c:txtexp))
(command "_layer" "set" "nitride" "")
(command "_layer" "set" "text" "")
(command-s "_text" "2220.872,963.3" "2" "-90" "amplitude = 135 nm" )
(sssetfirst nil (ssget "_L"))
(if (not (numberp (vl-string-search "Mac" (getvar "platform")))) (c:txtexp))
(command "_layer" "set" "nitride" "")
(command "_layer" "set" "text" "")
(command-s "_text" "2217.872,963.3" "2" "-90" "start width = 280 nm" )
(sssetfirst nil (ssget "_L"))
(if (not (numberp (vl-string-search "Mac" (getvar "platform")))) (c:txtexp))
(command "_layer" "set" "nitride" "")
(command "_layer" "set" "text" "")
(command-s "_text" "2214.872,963.3" "2" "-90" "width = 294 nm" )
(sssetfirst nil (ssget "_L"))
(if (not (numberp (vl-string-search "Mac" (getvar "platform")))) (c:txtexp))
(command "_layer" "set" "nitride" "")
(command "_layer" "set" "text" "")
(command-s "_text" "2211.872,963.3" "2" "-90" "taper: 15" )
(sssetfirst nil (ssget "_L"))
(if (not (numberp (vl-string-search "Mac" (getvar "platform")))) (c:txtexp))
(command "_layer" "set" "nitride" "")
(command "_layer" "set" "text" "")
(command-s "_text" "2208.872,963.3" "2" "-90" "nominal: 150" )
(sssetfirst nil (ssget "_L"))
(if (not (numberp (vl-string-search "Mac" (getvar "platform")))) (c:txtexp))
(command "_layer" "set" "nitride" "")
(command "_layer" "set" "indicators" "")
(setq coords (list 
(list 2160.415 940) 
(list 2160.415 920) 
(list 2140.415 900) 
(list 2160.415 880) 
(list 2160.415 860) 
(list 2160.415 900) 
(list 2160.415 887.0711) 
(list 2147.4861 900) 
(list 2160.415 912.9289) 
(list 2160.415 900)))
(apply 'command (append '("pline") coords '("c")))
(command "._fillet" "radius" "1" "._fillet" "P" (entlast))
(setq coords (list 
(list 2319.585 940) 
(list 2319.585 920) 
(list 2339.585 900) 
(list 2319.585 880) 
(list 2319.585 860) 
(list 2319.585 900) 
(list 2319.585 887.0711) 
(list 2332.5139 900) 
(list 2319.585 912.9289) 
(list 2319.585 900)))
(apply 'command (append '("pline") coords '("c")))
(command "._fillet" "radius" "1" "._fillet" "P" (entlast))
(command "_layer" "set" "holes" "")
(command "_circle" "2158.0629,914.1124" "0.5")
(command "_circle" "2155.7109,911.7603" "0.5")
(command "_circle" "2153.3588,909.4083" "0.5")
(command "_circle" "2151.0067,907.0562" "0.5")
(command "_circle" "2148.6547,904.7041" "0.5")
(command "_circle" "2146.3026,902.3521" "0.5")
(command "_circle" "2143.9505,900" "0.5")
(command "_circle" "2146.3026,897.6479" "0.5")
(command "_circle" "2148.6547,895.2959" "0.5")
(command "_circle" "2151.0067,892.9438" "0.5")
(command "_circle" "2153.3588,890.5917" "0.5")
(command "_circle" "2155.7109,888.2397" "0.5")
(command "_circle" "2158.0629,885.8876" "0.5")
(command "_circle" "2321.9371,914.1124" "0.5")
(command "_circle" "2324.2891,911.7603" "0.5")
(command "_circle" "2326.6412,909.4083" "0.5")
(command "_circle" "2328.9933,907.0562" "0.5")
(command "_circle" "2331.3453,904.7041" "0.5")
(command "_circle" "2333.6974,902.3521" "0.5")
(command "_circle" "2336.0495,900" "0.5")
(command "_circle" "2333.6974,897.6479" "0.5")
(command "_circle" "2331.3453,895.2959" "0.5")
(command "_circle" "2328.9933,892.9438" "0.5")
(command "_circle" "2326.6412,890.5917" "0.5")
(command "_circle" "2324.2891,888.2397" "0.5")
(command "_circle" "2321.9371,885.8876" "0.5")
(command "_layer" "set" "nitride" "")
(command "_block" "blkcoupler7" "2240,900" coupler7 "")
(command "_insert" "blkcoupler7" "2240,900" "1" "1" "0")
(command "_insert" "blkcoupler7" "2240,900" "1" "1" "180")
(command "_block" "blksinglenanobeam7" "2240,900" singlenanobeam7 "")
(command "_insert" "blksinglenanobeam7" "2240,900" "1" "1" "0")
(command "_insert" "blksinglenanobeam7" "2240,900" "1" "1" "180")
(command "_block" "blkanglednodearray7" "2240,900" anglednodearray7 "")
(command "_insert" "blkanglednodearray7" "2240,900" "1" "1" "0")
(command "_insert" "blkanglednodearray7" "2240,900" "1" "1" "180")
(command "_block" "blkcooledsinglenanobeam7" "2240,900" cooledsinglenanobeam7 "")
(command "_insert" "blkcooledsinglenanobeam7" "2240,900" "1" "1" "0")
(command "_insert" "blkcooledsinglenanobeam7" "2240,900" "1" "1" "180")
(command "_block" "blkyjunction7" "2240,900" yjunction7 "")
(command "_insert" "blkyjunction7" "2240,900" "1" "1" "0")
(command "_insert" "blkyjunction7" "2240,900" "1" "1" "180")
; DRAWING BULGING VEE GROOVE
(command "_layer" "set" "vgroove" "")
(setq coords (list 
(list 2165.415 -605) 
(list 2165.415 0) 
(list 2165.415 0) 
(list 2165.415 1800) 
(list 2165.415 1800) 
(list 2165.415 2405) 
(list 2314.585 2405) 
(list 2314.585 1800) 
(list 2314.585 1800) 
(list 2314.585 0) 
(list 2314.585 0) 
(list 2314.585 -605)))
(apply 'command (append '("pline") coords '("c")))
(command "._fillet" "radius" "0" "._fillet" "P" (entlast))
(command "_layer" "set" "window" "")
(command "_rectangle" "2165.415,-1935" "2314.585,-600")
(command "_rectangle" "2165.415,2400" "2314.585,5300")
(command "_layer" "set" "grid" "")
(command "_rectangle" "2166.415,-1934" "2189.9433,-1909.2133")
(command "_array" "last" "" "R" "75" "3" "25.7867" "24.5283")
(command "_rectangle" "2241,-1934" "2264.5283,-1909.2133")
(command "_array" "last" "" "R" "75" "3" "25.7867" "24.5283")
(command "_rectangle" "2166.415,1" "2189.9433,25.7")
(command "_array" "last" "" "R" "70" "3" "25.7" "24.5283")
(command "_rectangle" "2241,1" "2264.5283,25.7")
(command "_array" "last" "" "R" "70" "3" "25.7" "24.5283")
(command "_rectangle" "2166.415,1801" "2189.9433,1825.9185")
(command "_array" "last" "" "R" "135" "3" "25.9185" "24.5283")
(command "_rectangle" "2241,1801" "2264.5283,1825.9185")
(command "_array" "last" "" "R" "135" "3" "25.9185" "24.5283")
(command "_layer" "set" "vgrooveFDA" "")
(command "_rectangle" "2314.585,-2233" "2165.415,-1933")
(command "_layer" "set" "nitride" "")
(command "_layer" "set" "holes" "")
(command "_circle" "2317.085,331.5" "0.5")
(command "_array" "last" "" "R" "379" "1" "3" "2.5")
(command "_circle" "2162.915,331.5" "0.5")
(command "_array" "last" "" "R" "379" "1" "3" "-2.5")
(command "_layer" "set" "nitride" "")
(command "_layer" "set" "window" "")
(command "_layer" "set" "window" "")
(command "_rectangle" "2319.585,0" "2480.415,1800")
(command "._fillet" "radius" "20" "._fillet" "P" (entlast))
(command "_layer" "set" "grid" "")
(command "_rectangle" "2320.585,1" "2342.4179,25.7")
(command "_array" "last" "" "R" "70" "7" "25.7" "22.8329")
(command "_layer" "set" "nitride" "")
; DRAWING REGION LAYER
(command "_layer" "set" "regionLayer7" "")
(command "_rectangle" "2160,-460" "2320,2260")
(command "_layer" "set" "nitride" "")
(setq coupler7 nil)
(setq singlenanobeam7 nil)
(setq anglednodearray7 nil)
(setq cooledsinglenanobeam7 nil)
(setq yjunction7 nil)
; DEVICE #8
(command "_layer" "set" "window" "")
(command "_circle" "2472.915,-415" "5")
(command "_circle" "2472.915,-402.5" "5")
(command "_circle" "2472.915,-390" "5")
(command "_circle" "2472.915,-377.5" "5")
(command "_circle" "2460.415,-415" "5")
(command "_circle" "2460.415,-402.5" "5")
(command "_circle" "2460.415,-390" "5")
(command "_circle" "2460.415,-377.5" "5")
(command "_layer" "set" "nitride" "")
(setq currobj nil)
(setq currobj (ssadd))
; DRAWING COUPLER
(setq coords (list 
(list 2560.0645 -415) 
(list 2560.0645 -413) 
(list 2633.585 -413) 
(list 2633.585 -413) 
(list 2633.9677 -413.0761) 
(list 2634.2921 -413.2929) 
(list 2634.5089 -413.6173) 
(list 2634.585 -414) 
(list 2634.585 -411.8) 
(list 2634.585 -411.8) 
(list 2634.5089 -412.1827) 
(list 2634.2921 -412.5071) 
(list 2633.9677 -412.7239) 
(list 2633.585 -412.8) 
(list 2560.0645 -412.8) 
(list 2560.0645 -410.8) 
(list 2559.9355 -410.8) 
(list 2559.9355 -412.8) 
(list 2486.415 -412.8) 
(list 2486.0323 -412.7239) 
(list 2485.7079 -412.5071) 
(list 2485.4911 -412.1827) 
(list 2485.415 -411.8) 
(list 2485.415 -411.8) 
(list 2485.415 -414) 
(list 2485.4911 -413.6173) 
(list 2485.7079 -413.2929) 
(list 2486.0323 -413.0761) 
(list 2486.415 -413) 
(list 2486.415 -413) 
(list 2559.9355 -413) 
(list 2559.9355 -415)))
(apply 'command (append '("pline") coords '("c")))
(setq currobj (ssadd (entlast) currobj))
(command "._fillet" "radius" "0.3" "._fillet" "P" (entlast))
(command "_layer" "set" "holes" "")
(command "_circle" "2560,-412.9" "0.113")
(setq currobj (ssadd (entlast) currobj))
(command "_layer" "set" "nitride" "")
(command "_layer" "set" "text" "")
(command "_circle" "2559.2,-415" "0.075")
(command "_circle" "2559.2,-414.7" "0.075")
(command "_circle" "2559.2,-414.4" "0.075")
(command "_circle" "2558.9,-415" "0.075")
(command "_circle" "2558.9,-414.7" "0.075")
(command "_circle" "2558.9,-414.4" "0.075")
(command "_circle" "2558.6,-415" "0.075")
(command "_circle" "2558.6,-414.7" "0.075")
(command "_circle" "2558.6,-414.4" "0.075")
(command "_layer" "set" "nitride" "")
(command "_layer" "set" "prebias" "")
(command "_rectangle" "2485.415,-414" "2634.585,-411.8")
(setq currobj (ssadd (entlast) currobj))
(command "_rectangle" "2559.9355,-415" "2560.0645,-410.8")
(setq currobj (ssadd (entlast) currobj))
(command "_layer" "set" "nitride" "")
(setq coupler8 currobj)
(setq currobj nil)
(setq currobj (ssadd))
; DRAWING SINGLE NANOBEAM
(setq coords (list 
(list 2560.0645 -410.8) 
(list 2560.0645 -409.1417) 
(list 2560.0645 -407.4833) 
(list 2560.0645 -405.825) 
(list 2560.0645 -404.1667) 
(list 2560.0645 -402.5083) 
(list 2560.0645 -400.85) 
(list 2560.0645 -399.1917) 
(list 2560.0645 -397.5333) 
(list 2560.0646 -395.875) 
(list 2560.0646 -394.2167) 
(list 2560.0646 -392.5583) 
(list 2560.0646 -390.9) 
(list 2560.0647 -389.2417) 
(list 2560.0647 -387.5833) 
(list 2560.0647 -385.925) 
(list 2560.0648 -384.2667) 
(list 2560.0648 -382.6083) 
(list 2560.0649 -380.95) 
(list 2560.065 -379.2917) 
(list 2560.0651 -377.6333) 
(list 2560.0651 -375.975) 
(list 2560.0652 -374.3167) 
(list 2560.0653 -372.6583) 
(list 2560.0655 -371) 
(list 2560.0656 -369.3417) 
(list 2560.0657 -367.6833) 
(list 2560.0659 -366.025) 
(list 2560.066 -364.3667) 
(list 2560.0662 -362.7083) 
(list 2560.0664 -361.05) 
(list 2560.0666 -359.3917) 
(list 2560.0668 -357.7333) 
(list 2560.067 -356.075) 
(list 2560.0672 -354.4167) 
(list 2560.0675 -352.7583) 
(list 2560.0678 -351.1) 
(list 2560.068 -349.4417) 
(list 2560.0683 -347.7833) 
(list 2560.0686 -346.125) 
(list 2560.069 -344.4667) 
(list 2560.0693 -342.8083) 
(list 2560.0697 -341.15) 
(list 2560.07 -339.4917) 
(list 2560.0704 -337.8333) 
(list 2560.0709 -336.175) 
(list 2560.0713 -334.5167) 
(list 2560.0717 -332.8583) 
(list 2560.0722 -331.2) 
(list 2560.0727 -329.5417) 
(list 2560.0732 -327.8833) 
(list 2560.0738 -326.225) 
(list 2560.0743 -324.5667) 
(list 2560.0749 -322.9083) 
(list 2560.0755 -321.25) 
(list 2560.0761 -319.5917) 
(list 2560.0767 -317.9333) 
(list 2560.0774 -316.275) 
(list 2560.0781 -314.6167) 
(list 2560.0788 -312.9583) 
(list 2560.0796 -311.3) 
(list 2560.0803 -309.6417) 
(list 2560.0811 -307.9833) 
(list 2560.0819 -306.325) 
(list 2560.0828 -304.6667) 
(list 2560.0837 -303.0083) 
(list 2560.0845 -301.35) 
(list 2560.0855 -299.6917) 
(list 2560.0864 -298.0333) 
(list 2560.0874 -296.375) 
(list 2560.0884 -294.7167) 
(list 2560.0895 -293.0583) 
(list 2560.0905 -291.4) 
(list 2560.0916 -289.7417) 
(list 2560.0928 -288.0833) 
(list 2560.0939 -286.425) 
(list 2560.0951 -284.7667) 
(list 2560.0963 -283.1083) 
(list 2560.0976 -281.45) 
(list 2560.0989 -279.7917) 
(list 2560.1002 -278.1333) 
(list 2560.1016 -276.475) 
(list 2560.1029 -274.8167) 
(list 2560.1044 -273.1583) 
(list 2560.1058 -271.5) 
(list 2560.1073 -269.8417) 
(list 2560.1089 -268.1833) 
(list 2560.1104 -266.525) 
(list 2560.112 -264.8667) 
(list 2560.1137 -263.2083) 
(list 2560.1153 -261.55) 
(list 2560.117 -259.8917) 
(list 2560.1188 -258.2333) 
(list 2560.1206 -256.575) 
(list 2560.1224 -254.9167) 
(list 2560.1243 -253.2583) 
(list 2560.1262 -251.6) 
(list 2560.1281 -249.9417) 
(list 2560.1301 -248.2833) 
(list 2560.1322 -246.625) 
(list 2560.1342 -244.9667) 
(list 2560.1363 -243.3083) 
(list 2560.1385 -241.65) 
(list 2560.1407 -239.9917) 
(list 2560.1429 -238.3333) 
(list 2560.1452 -236.675) 
(list 2560.1476 -235.0167) 
(list 2560.1499 -233.3583) 
(list 2560.1523 -231.7) 
(list 2560.1548 -230.0417) 
(list 2560.1573 -228.3833) 
(list 2560.1599 -226.725) 
(list 2560.1625 -225.0667) 
(list 2560.1651 -223.4083) 
(list 2560.1678 -221.75) 
(list 2560.1706 -220.0917) 
(list 2560.1733 -218.4333) 
(list 2560.1762 -216.775) 
(list 2560.1791 -215.1167) 
(list 2560.182 -213.4583) 
(list 2560.185 -211.8) 
(list 2559.815 -211.8) 
(list 2559.818 -213.4583) 
(list 2559.8209 -215.1167) 
(list 2559.8238 -216.775) 
(list 2559.8267 -218.4333) 
(list 2559.8294 -220.0917) 
(list 2559.8322 -221.75) 
(list 2559.8349 -223.4083) 
(list 2559.8375 -225.0667) 
(list 2559.8401 -226.725) 
(list 2559.8427 -228.3833) 
(list 2559.8452 -230.0417) 
(list 2559.8477 -231.7) 
(list 2559.8501 -233.3583) 
(list 2559.8524 -235.0167) 
(list 2559.8548 -236.675) 
(list 2559.8571 -238.3333) 
(list 2559.8593 -239.9917) 
(list 2559.8615 -241.65) 
(list 2559.8637 -243.3083) 
(list 2559.8658 -244.9667) 
(list 2559.8678 -246.625) 
(list 2559.8699 -248.2833) 
(list 2559.8719 -249.9417) 
(list 2559.8738 -251.6) 
(list 2559.8757 -253.2583) 
(list 2559.8776 -254.9167) 
(list 2559.8794 -256.575) 
(list 2559.8812 -258.2333) 
(list 2559.883 -259.8917) 
(list 2559.8847 -261.55) 
(list 2559.8863 -263.2083) 
(list 2559.888 -264.8667) 
(list 2559.8896 -266.525) 
(list 2559.8911 -268.1833) 
(list 2559.8927 -269.8417) 
(list 2559.8942 -271.5) 
(list 2559.8956 -273.1583) 
(list 2559.8971 -274.8167) 
(list 2559.8984 -276.475) 
(list 2559.8998 -278.1333) 
(list 2559.9011 -279.7917) 
(list 2559.9024 -281.45) 
(list 2559.9037 -283.1083) 
(list 2559.9049 -284.7667) 
(list 2559.9061 -286.425) 
(list 2559.9072 -288.0833) 
(list 2559.9084 -289.7417) 
(list 2559.9095 -291.4) 
(list 2559.9105 -293.0583) 
(list 2559.9116 -294.7167) 
(list 2559.9126 -296.375) 
(list 2559.9136 -298.0333) 
(list 2559.9145 -299.6917) 
(list 2559.9155 -301.35) 
(list 2559.9163 -303.0083) 
(list 2559.9172 -304.6667) 
(list 2559.9181 -306.325) 
(list 2559.9189 -307.9833) 
(list 2559.9197 -309.6417) 
(list 2559.9204 -311.3) 
(list 2559.9212 -312.9583) 
(list 2559.9219 -314.6167) 
(list 2559.9226 -316.275) 
(list 2559.9233 -317.9333) 
(list 2559.9239 -319.5917) 
(list 2559.9245 -321.25) 
(list 2559.9251 -322.9083) 
(list 2559.9257 -324.5667) 
(list 2559.9262 -326.225) 
(list 2559.9268 -327.8833) 
(list 2559.9273 -329.5417) 
(list 2559.9278 -331.2) 
(list 2559.9283 -332.8583) 
(list 2559.9287 -334.5167) 
(list 2559.9291 -336.175) 
(list 2559.9296 -337.8333) 
(list 2559.93 -339.4917) 
(list 2559.9303 -341.15) 
(list 2559.9307 -342.8083) 
(list 2559.931 -344.4667) 
(list 2559.9314 -346.125) 
(list 2559.9317 -347.7833) 
(list 2559.932 -349.4417) 
(list 2559.9322 -351.1) 
(list 2559.9325 -352.7583) 
(list 2559.9328 -354.4167) 
(list 2559.933 -356.075) 
(list 2559.9332 -357.7333) 
(list 2559.9334 -359.3917) 
(list 2559.9336 -361.05) 
(list 2559.9338 -362.7083) 
(list 2559.934 -364.3667) 
(list 2559.9341 -366.025) 
(list 2559.9343 -367.6833) 
(list 2559.9344 -369.3417) 
(list 2559.9345 -371) 
(list 2559.9347 -372.6583) 
(list 2559.9348 -374.3167) 
(list 2559.9349 -375.975) 
(list 2559.9349 -377.6333) 
(list 2559.935 -379.2917) 
(list 2559.9351 -380.95) 
(list 2559.9352 -382.6083) 
(list 2559.9352 -384.2667) 
(list 2559.9353 -385.925) 
(list 2559.9353 -387.5833) 
(list 2559.9353 -389.2417) 
(list 2559.9354 -390.9) 
(list 2559.9354 -392.5583) 
(list 2559.9354 -394.2167) 
(list 2559.9354 -395.875) 
(list 2559.9355 -397.5333) 
(list 2559.9355 -399.1917) 
(list 2559.9355 -400.85) 
(list 2559.9355 -402.5083) 
(list 2559.9355 -404.1667) 
(list 2559.9355 -405.825) 
(list 2559.9355 -407.4833) 
(list 2559.9355 -409.1417) 
(list 2559.9355 -410.8)))
(apply 'command (append '("pline") coords '("c")))
(setq currobj (ssadd (entlast) currobj))
(command "_layer" "set" "prebias" "")
(command "_rectangle" "2559.815,-410.8" "2560.185,-211.8")
(setq currobj (ssadd (entlast) currobj))
(command "_layer" "set" "nitride" "")
(setq singlenanobeam8 currobj)
(setq currobj nil)
(setq currobj (ssadd))
; DRAWING NODE ARRAY
(setq coords (list 
(list 2560.185 -211.8) 
(list 2560.5625 -201.8) 
(list 2560.5625 -201.8) 
(list 2560.5625 -200.8) 
(list 2634.585 -212.6864) 
(list 2634.585 -207.7434) 
(list 2560.5625 -197.357) 
(list 2560.5625 -196.357) 
(list 2560.5625 -196.357) 
(list 2560.2625 -186.357) 
(list 2559.7375 -186.357) 
(list 2559.4375 -196.357) 
(list 2559.4375 -196.357) 
(list 2559.4375 -197.357) 
(list 2485.415 -207.7434) 
(list 2485.415 -212.6864) 
(list 2559.4375 -200.8) 
(list 2559.4375 -201.8) 
(list 2559.4375 -201.8) 
(list 2559.815 -211.8)))
(apply 'command (append '("pline") coords '("c")))
(setq currobj (ssadd (entlast) currobj))
(command "_layer" "set" "prebias" "")
(setq coords (list 
(list 2559.4375 -212.6864) 
(list 2559.4375 -200.8) 
(list 2485.415 -212.6864) 
(list 2485.415 -207.7434) 
(list 2559.4375 -197.357) 
(list 2559.4375 -186.357) 
(list 2560.5625 -186.357) 
(list 2560.5625 -197.357) 
(list 2634.585 -207.7434) 
(list 2634.585 -212.6864) 
(list 2560.5625 -200.8) 
(list 2560.5625 -212.6864)))
(apply 'command (append '("pline") coords '("c")))
(setq currobj (ssadd (entlast) currobj))
(command "_layer" "set" "nitride" "")
(command "_layer" "set" "fda1" "")
(setq coords (list 
(list 2560.5625 -200.657) 
(list 2634.585 -212.5434) 
(list 2634.585 -212.3664) 
(list 2560.5625 -200.58)))
(apply 'command (append '("pline") coords '("c")))
(setq currobj (ssadd (entlast) currobj))
(setq coords (list 
(list 2560.5625 -200.437) 
(list 2634.585 -212.2234) 
(list 2634.585 -212.0464) 
(list 2560.5625 -200.36)))
(apply 'command (append '("pline") coords '("c")))
(setq currobj (ssadd (entlast) currobj))
(setq coords (list 
(list 2560.5625 -200.217) 
(list 2634.585 -211.9034) 
(list 2634.585 -211.7264) 
(list 2560.5625 -200.14)))
(apply 'command (append '("pline") coords '("c")))
(setq currobj (ssadd (entlast) currobj))
(setq coords (list 
(list 2560.5625 -199.997) 
(list 2634.585 -211.5834) 
(list 2634.585 -211.4064) 
(list 2560.5625 -199.92)))
(apply 'command (append '("pline") coords '("c")))
(setq currobj (ssadd (entlast) currobj))
(setq coords (list 
(list 2560.5625 -199.777) 
(list 2634.585 -211.2634) 
(list 2634.585 -211.0864) 
(list 2560.5625 -199.7)))
(apply 'command (append '("pline") coords '("c")))
(setq currobj (ssadd (entlast) currobj))
(setq coords (list 
(list 2560.5625 -199.557) 
(list 2634.585 -210.9434) 
(list 2634.585 -210.7664) 
(list 2560.5625 -199.48)))
(apply 'command (append '("pline") coords '("c")))
(setq currobj (ssadd (entlast) currobj))
(setq coords (list 
(list 2560.5625 -199.337) 
(list 2634.585 -210.6234) 
(list 2634.585 -210.4464) 
(list 2560.5625 -199.26)))
(apply 'command (append '("pline") coords '("c")))
(setq currobj (ssadd (entlast) currobj))
(setq coords (list 
(list 2560.5625 -199.117) 
(list 2634.585 -210.3034) 
(list 2634.585 -210.1264) 
(list 2560.5625 -199.04)))
(apply 'command (append '("pline") coords '("c")))
(setq currobj (ssadd (entlast) currobj))
(setq coords (list 
(list 2560.5625 -198.897) 
(list 2634.585 -209.9834) 
(list 2634.585 -209.8064) 
(list 2560.5625 -198.82)))
(apply 'command (append '("pline") coords '("c")))
(setq currobj (ssadd (entlast) currobj))
(setq coords (list 
(list 2560.5625 -198.677) 
(list 2634.585 -209.6634) 
(list 2634.585 -209.4864) 
(list 2560.5625 -198.6)))
(apply 'command (append '("pline") coords '("c")))
(setq currobj (ssadd (entlast) currobj))
(setq coords (list 
(list 2560.5625 -198.457) 
(list 2634.585 -209.3434) 
(list 2634.585 -209.1664) 
(list 2560.5625 -198.38)))
(apply 'command (append '("pline") coords '("c")))
(setq currobj (ssadd (entlast) currobj))
(setq coords (list 
(list 2560.5625 -198.237) 
(list 2634.585 -209.0234) 
(list 2634.585 -208.8464) 
(list 2560.5625 -198.16)))
(apply 'command (append '("pline") coords '("c")))
(setq currobj (ssadd (entlast) currobj))
(setq coords (list 
(list 2560.5625 -198.017) 
(list 2634.585 -208.7034) 
(list 2634.585 -208.5264) 
(list 2560.5625 -197.94)))
(apply 'command (append '("pline") coords '("c")))
(setq currobj (ssadd (entlast) currobj))
(setq coords (list 
(list 2560.5625 -197.797) 
(list 2634.585 -208.3834) 
(list 2634.585 -208.2064) 
(list 2560.5625 -197.72)))
(apply 'command (append '("pline") coords '("c")))
(setq currobj (ssadd (entlast) currobj))
(setq coords (list 
(list 2560.5625 -197.577) 
(list 2634.585 -208.0634) 
(list 2634.585 -207.8864) 
(list 2560.5625 -197.5)))
(apply 'command (append '("pline") coords '("c")))
(setq currobj (ssadd (entlast) currobj))
(setq coords (list 
(list 2559.4375 -197.5) 
(list 2485.415 -207.8864) 
(list 2485.415 -208.0634) 
(list 2559.4375 -197.577)))
(apply 'command (append '("pline") coords '("c")))
(setq currobj (ssadd (entlast) currobj))
(setq coords (list 
(list 2559.4375 -197.72) 
(list 2485.415 -208.2064) 
(list 2485.415 -208.3834) 
(list 2559.4375 -197.797)))
(apply 'command (append '("pline") coords '("c")))
(setq currobj (ssadd (entlast) currobj))
(setq coords (list 
(list 2559.4375 -197.94) 
(list 2485.415 -208.5264) 
(list 2485.415 -208.7034) 
(list 2559.4375 -198.017)))
(apply 'command (append '("pline") coords '("c")))
(setq currobj (ssadd (entlast) currobj))
(setq coords (list 
(list 2559.4375 -198.16) 
(list 2485.415 -208.8464) 
(list 2485.415 -209.0234) 
(list 2559.4375 -198.237)))
(apply 'command (append '("pline") coords '("c")))
(setq currobj (ssadd (entlast) currobj))
(setq coords (list 
(list 2559.4375 -198.38) 
(list 2485.415 -209.1664) 
(list 2485.415 -209.3434) 
(list 2559.4375 -198.457)))
(apply 'command (append '("pline") coords '("c")))
(setq currobj (ssadd (entlast) currobj))
(setq coords (list 
(list 2559.4375 -198.6) 
(list 2485.415 -209.4864) 
(list 2485.415 -209.6634) 
(list 2559.4375 -198.677)))
(apply 'command (append '("pline") coords '("c")))
(setq currobj (ssadd (entlast) currobj))
(setq coords (list 
(list 2559.4375 -198.82) 
(list 2485.415 -209.8064) 
(list 2485.415 -209.9834) 
(list 2559.4375 -198.897)))
(apply 'command (append '("pline") coords '("c")))
(setq currobj (ssadd (entlast) currobj))
(setq coords (list 
(list 2559.4375 -199.04) 
(list 2485.415 -210.1264) 
(list 2485.415 -210.3034) 
(list 2559.4375 -199.117)))
(apply 'command (append '("pline") coords '("c")))
(setq currobj (ssadd (entlast) currobj))
(setq coords (list 
(list 2559.4375 -199.26) 
(list 2485.415 -210.4464) 
(list 2485.415 -210.6234) 
(list 2559.4375 -199.337)))
(apply 'command (append '("pline") coords '("c")))
(setq currobj (ssadd (entlast) currobj))
(setq coords (list 
(list 2559.4375 -199.48) 
(list 2485.415 -210.7664) 
(list 2485.415 -210.9434) 
(list 2559.4375 -199.557)))
(apply 'command (append '("pline") coords '("c")))
(setq currobj (ssadd (entlast) currobj))
(setq coords (list 
(list 2559.4375 -199.7) 
(list 2485.415 -211.0864) 
(list 2485.415 -211.2634) 
(list 2559.4375 -199.777)))
(apply 'command (append '("pline") coords '("c")))
(setq currobj (ssadd (entlast) currobj))
(setq coords (list 
(list 2559.4375 -199.92) 
(list 2485.415 -211.4064) 
(list 2485.415 -211.5834) 
(list 2559.4375 -199.997)))
(apply 'command (append '("pline") coords '("c")))
(setq currobj (ssadd (entlast) currobj))
(setq coords (list 
(list 2559.4375 -200.14) 
(list 2485.415 -211.7264) 
(list 2485.415 -211.9034) 
(list 2559.4375 -200.217)))
(apply 'command (append '("pline") coords '("c")))
(setq currobj (ssadd (entlast) currobj))
(setq coords (list 
(list 2559.4375 -200.36) 
(list 2485.415 -212.0464) 
(list 2485.415 -212.2234) 
(list 2559.4375 -200.437)))
(apply 'command (append '("pline") coords '("c")))
(setq currobj (ssadd (entlast) currobj))
(setq coords (list 
(list 2559.4375 -200.58) 
(list 2485.415 -212.3664) 
(list 2485.415 -212.5434) 
(list 2559.4375 -200.657)))
(apply 'command (append '("pline") coords '("c")))
(setq currobj (ssadd (entlast) currobj))
(command "_layer" "set" "nitride" "")
(command "_layer" "set" "text" "")
(command "_circle" "2558.985,-211.8" "0.075")
(command "_circle" "2558.985,-211.5" "0.075")
(command "_circle" "2558.985,-211.2" "0.075")
(command "_circle" "2558.985,-210.9" "0.075")
(command "_circle" "2558.985,-210.6" "0.075")
(command "_circle" "2558.685,-211.8" "0.075")
(command "_circle" "2558.685,-211.5" "0.075")
(command "_circle" "2558.685,-211.2" "0.075")
(command "_circle" "2558.685,-210.9" "0.075")
(command "_circle" "2558.685,-210.6" "0.075")
(command "_circle" "2558.385,-211.8" "0.075")
(command "_circle" "2558.385,-211.5" "0.075")
(command "_circle" "2558.385,-211.2" "0.075")
(command "_circle" "2558.385,-210.9" "0.075")
(command "_circle" "2558.385,-210.6" "0.075")
(command "_circle" "2558.085,-211.8" "0.075")
(command "_circle" "2558.085,-211.5" "0.075")
(command "_circle" "2558.085,-211.2" "0.075")
(command "_circle" "2558.085,-210.9" "0.075")
(command "_circle" "2558.085,-210.6" "0.075")
(command "_circle" "2557.785,-211.8" "0.075")
(command "_circle" "2557.785,-211.5" "0.075")
(command "_circle" "2557.785,-211.2" "0.075")
(command "_circle" "2557.785,-210.9" "0.075")
(command "_circle" "2557.785,-210.6" "0.075")
(command "_layer" "set" "nitride" "")
(setq anglednodearray8 currobj)
(setq currobj nil)
(setq currobj (ssadd))
; DRAWING COOLED SINGLE NANOBEAM
(setq coords (list 
(list 2560.2625 -186.357) 
(list 2560.2625 -181.357) 
(list 2559.7375 -181.357) 
(list 2559.7375 -186.357)))
(apply 'command (append '("pline") coords '("c")))
(setq currobj (ssadd (entlast) currobj))
(command "_layer" "set" "prebias" "")
(command "_rectangle" "2559.7375,-186.357" "2560.2625,-181.357")
(setq currobj (ssadd (entlast) currobj))
(command "_layer" "set" "nitride" "")
(setq coords (list 
(list 2560.2625 -181.357) 
(list 2560.5625 -171.357) 
(list 2560.5625 -171.357) 
(list 2560.5625 -170.357) 
(list 2634.585 -171.107) 
(list 2634.585 -166.164) 
(list 2560.5625 -166.914) 
(list 2560.5625 -165.914) 
(list 2560.5625 -165.914) 
(list 2560.2625 -155.914) 
(list 2559.7375 -155.914) 
(list 2559.4375 -165.914) 
(list 2559.4375 -165.914) 
(list 2559.4375 -166.914) 
(list 2485.415 -166.164) 
(list 2485.415 -171.107) 
(list 2559.4375 -170.357) 
(list 2559.4375 -171.357) 
(list 2559.4375 -171.357) 
(list 2559.7375 -181.357)))
(apply 'command (append '("pline") coords '("c")))
(setq currobj (ssadd (entlast) currobj))
(command "_layer" "set" "prebias" "")
(setq coords (list 
(list 2559.4375 -181.357) 
(list 2559.4375 -170.357) 
(list 2485.415 -171.107) 
(list 2485.415 -166.164) 
(list 2559.4375 -166.914) 
(list 2559.4375 -155.914) 
(list 2560.5625 -155.914) 
(list 2560.5625 -166.914) 
(list 2634.585 -166.164) 
(list 2634.585 -171.107) 
(list 2560.5625 -170.357) 
(list 2560.5625 -181.357)))
(apply 'command (append '("pline") coords '("c")))
(setq currobj (ssadd (entlast) currobj))
(command "_layer" "set" "nitride" "")
(command "_layer" "set" "fda1" "")
(setq coords (list 
(list 2560.5625 -170.214) 
(list 2634.585 -170.964) 
(list 2634.585 -170.787) 
(list 2560.5625 -170.137)))
(apply 'command (append '("pline") coords '("c")))
(setq currobj (ssadd (entlast) currobj))
(setq coords (list 
(list 2560.5625 -169.994) 
(list 2634.585 -170.644) 
(list 2634.585 -170.467) 
(list 2560.5625 -169.917)))
(apply 'command (append '("pline") coords '("c")))
(setq currobj (ssadd (entlast) currobj))
(setq coords (list 
(list 2560.5625 -169.774) 
(list 2634.585 -170.324) 
(list 2634.585 -170.147) 
(list 2560.5625 -169.697)))
(apply 'command (append '("pline") coords '("c")))
(setq currobj (ssadd (entlast) currobj))
(setq coords (list 
(list 2560.5625 -169.554) 
(list 2634.585 -170.004) 
(list 2634.585 -169.827) 
(list 2560.5625 -169.477)))
(apply 'command (append '("pline") coords '("c")))
(setq currobj (ssadd (entlast) currobj))
(setq coords (list 
(list 2560.5625 -169.334) 
(list 2634.585 -169.684) 
(list 2634.585 -169.507) 
(list 2560.5625 -169.257)))
(apply 'command (append '("pline") coords '("c")))
(setq currobj (ssadd (entlast) currobj))
(setq coords (list 
(list 2560.5625 -169.114) 
(list 2634.585 -169.364) 
(list 2634.585 -169.187) 
(list 2560.5625 -169.037)))
(apply 'command (append '("pline") coords '("c")))
(setq currobj (ssadd (entlast) currobj))
(setq coords (list 
(list 2560.5625 -168.894) 
(list 2634.585 -169.044) 
(list 2634.585 -168.867) 
(list 2560.5625 -168.817)))
(apply 'command (append '("pline") coords '("c")))
(setq currobj (ssadd (entlast) currobj))
(setq coords (list 
(list 2560.5625 -168.674) 
(list 2634.585 -168.724) 
(list 2634.585 -168.547) 
(list 2560.5625 -168.597)))
(apply 'command (append '("pline") coords '("c")))
(setq currobj (ssadd (entlast) currobj))
(setq coords (list 
(list 2560.5625 -168.454) 
(list 2634.585 -168.404) 
(list 2634.585 -168.227) 
(list 2560.5625 -168.377)))
(apply 'command (append '("pline") coords '("c")))
(setq currobj (ssadd (entlast) currobj))
(setq coords (list 
(list 2560.5625 -168.234) 
(list 2634.585 -168.084) 
(list 2634.585 -167.907) 
(list 2560.5625 -168.157)))
(apply 'command (append '("pline") coords '("c")))
(setq currobj (ssadd (entlast) currobj))
(setq coords (list 
(list 2560.5625 -168.014) 
(list 2634.585 -167.764) 
(list 2634.585 -167.587) 
(list 2560.5625 -167.937)))
(apply 'command (append '("pline") coords '("c")))
(setq currobj (ssadd (entlast) currobj))
(setq coords (list 
(list 2560.5625 -167.794) 
(list 2634.585 -167.444) 
(list 2634.585 -167.267) 
(list 2560.5625 -167.717)))
(apply 'command (append '("pline") coords '("c")))
(setq currobj (ssadd (entlast) currobj))
(setq coords (list 
(list 2560.5625 -167.574) 
(list 2634.585 -167.124) 
(list 2634.585 -166.947) 
(list 2560.5625 -167.497)))
(apply 'command (append '("pline") coords '("c")))
(setq currobj (ssadd (entlast) currobj))
(setq coords (list 
(list 2560.5625 -167.354) 
(list 2634.585 -166.804) 
(list 2634.585 -166.627) 
(list 2560.5625 -167.277)))
(apply 'command (append '("pline") coords '("c")))
(setq currobj (ssadd (entlast) currobj))
(setq coords (list 
(list 2560.5625 -167.134) 
(list 2634.585 -166.484) 
(list 2634.585 -166.307) 
(list 2560.5625 -167.057)))
(apply 'command (append '("pline") coords '("c")))
(setq currobj (ssadd (entlast) currobj))
(setq coords (list 
(list 2559.4375 -167.057) 
(list 2485.415 -166.307) 
(list 2485.415 -166.484) 
(list 2559.4375 -167.134)))
(apply 'command (append '("pline") coords '("c")))
(setq currobj (ssadd (entlast) currobj))
(setq coords (list 
(list 2559.4375 -167.277) 
(list 2485.415 -166.627) 
(list 2485.415 -166.804) 
(list 2559.4375 -167.354)))
(apply 'command (append '("pline") coords '("c")))
(setq currobj (ssadd (entlast) currobj))
(setq coords (list 
(list 2559.4375 -167.497) 
(list 2485.415 -166.947) 
(list 2485.415 -167.124) 
(list 2559.4375 -167.574)))
(apply 'command (append '("pline") coords '("c")))
(setq currobj (ssadd (entlast) currobj))
(setq coords (list 
(list 2559.4375 -167.717) 
(list 2485.415 -167.267) 
(list 2485.415 -167.444) 
(list 2559.4375 -167.794)))
(apply 'command (append '("pline") coords '("c")))
(setq currobj (ssadd (entlast) currobj))
(setq coords (list 
(list 2559.4375 -167.937) 
(list 2485.415 -167.587) 
(list 2485.415 -167.764) 
(list 2559.4375 -168.014)))
(apply 'command (append '("pline") coords '("c")))
(setq currobj (ssadd (entlast) currobj))
(setq coords (list 
(list 2559.4375 -168.157) 
(list 2485.415 -167.907) 
(list 2485.415 -168.084) 
(list 2559.4375 -168.234)))
(apply 'command (append '("pline") coords '("c")))
(setq currobj (ssadd (entlast) currobj))
(setq coords (list 
(list 2559.4375 -168.377) 
(list 2485.415 -168.227) 
(list 2485.415 -168.404) 
(list 2559.4375 -168.454)))
(apply 'command (append '("pline") coords '("c")))
(setq currobj (ssadd (entlast) currobj))
(setq coords (list 
(list 2559.4375 -168.597) 
(list 2485.415 -168.547) 
(list 2485.415 -168.724) 
(list 2559.4375 -168.674)))
(apply 'command (append '("pline") coords '("c")))
(setq currobj (ssadd (entlast) currobj))
(setq coords (list 
(list 2559.4375 -168.817) 
(list 2485.415 -168.867) 
(list 2485.415 -169.044) 
(list 2559.4375 -168.894)))
(apply 'command (append '("pline") coords '("c")))
(setq currobj (ssadd (entlast) currobj))
(setq coords (list 
(list 2559.4375 -169.037) 
(list 2485.415 -169.187) 
(list 2485.415 -169.364) 
(list 2559.4375 -169.114)))
(apply 'command (append '("pline") coords '("c")))
(setq currobj (ssadd (entlast) currobj))
(setq coords (list 
(list 2559.4375 -169.257) 
(list 2485.415 -169.507) 
(list 2485.415 -169.684) 
(list 2559.4375 -169.334)))
(apply 'command (append '("pline") coords '("c")))
(setq currobj (ssadd (entlast) currobj))
(setq coords (list 
(list 2559.4375 -169.477) 
(list 2485.415 -169.827) 
(list 2485.415 -170.004) 
(list 2559.4375 -169.554)))
(apply 'command (append '("pline") coords '("c")))
(setq currobj (ssadd (entlast) currobj))
(setq coords (list 
(list 2559.4375 -169.697) 
(list 2485.415 -170.147) 
(list 2485.415 -170.324) 
(list 2559.4375 -169.774)))
(apply 'command (append '("pline") coords '("c")))
(setq currobj (ssadd (entlast) currobj))
(setq coords (list 
(list 2559.4375 -169.917) 
(list 2485.415 -170.467) 
(list 2485.415 -170.644) 
(list 2559.4375 -169.994)))
(apply 'command (append '("pline") coords '("c")))
(setq currobj (ssadd (entlast) currobj))
(setq coords (list 
(list 2559.4375 -170.137) 
(list 2485.415 -170.787) 
(list 2485.415 -170.964) 
(list 2559.4375 -170.214)))
(apply 'command (append '("pline") coords '("c")))
(setq currobj (ssadd (entlast) currobj))
(command "_layer" "set" "nitride" "")
(command "_layer" "set" "text" "")
(command "_circle" "2559.0625,-181.357" "0.075")
(command "_circle" "2559.0625,-181.057" "0.075")
(command "_circle" "2559.0625,-180.757" "0.075")
(command "_circle" "2559.0625,-180.457" "0.075")
(command "_circle" "2559.0625,-180.157" "0.075")
(command "_circle" "2558.7625,-181.357" "0.075")
(command "_circle" "2558.7625,-181.057" "0.075")
(command "_circle" "2558.7625,-180.757" "0.075")
(command "_circle" "2558.7625,-180.457" "0.075")
(command "_circle" "2558.7625,-180.157" "0.075")
(command "_circle" "2558.4625,-181.357" "0.075")
(command "_circle" "2558.4625,-181.057" "0.075")
(command "_circle" "2558.4625,-180.757" "0.075")
(command "_circle" "2558.4625,-180.457" "0.075")
(command "_circle" "2558.4625,-180.157" "0.075")
(command "_circle" "2558.1625,-181.357" "0.075")
(command "_circle" "2558.1625,-181.057" "0.075")
(command "_circle" "2558.1625,-180.757" "0.075")
(command "_circle" "2558.1625,-180.457" "0.075")
(command "_circle" "2558.1625,-180.157" "0.075")
(command "_circle" "2557.8625,-181.357" "0.075")
(command "_circle" "2557.8625,-181.057" "0.075")
(command "_circle" "2557.8625,-180.757" "0.075")
(command "_circle" "2557.8625,-180.457" "0.075")
(command "_circle" "2557.8625,-180.157" "0.075")
(command "_layer" "set" "nitride" "")
(setq coords (list 
(list 2560.2625 -155.914) 
(list 2560.2625 -40.2693) 
(list 2559.7375 -40.2693) 
(list 2559.7375 -155.914)))
(apply 'command (append '("pline") coords '("c")))
(setq currobj (ssadd (entlast) currobj))
(command "_layer" "set" "prebias" "")
(command "_rectangle" "2559.7375,-155.914" "2560.2625,-40.2693")
(setq currobj (ssadd (entlast) currobj))
(command "_layer" "set" "nitride" "")
(setq coords (list 
(list 2560.2625 -40.2693) 
(list 2560.5625 -30.2693) 
(list 2560.5625 -30.2693) 
(list 2560.5625 -29.2693) 
(list 2634.585 -30.0193) 
(list 2634.585 -25.0763) 
(list 2560.5625 -25.8263) 
(list 2560.5625 -24.8263) 
(list 2560.5625 -24.8263) 
(list 2560.2625 -14.8263) 
(list 2559.7375 -14.8263) 
(list 2559.4375 -24.8263) 
(list 2559.4375 -24.8263) 
(list 2559.4375 -25.8263) 
(list 2485.415 -25.0763) 
(list 2485.415 -30.0193) 
(list 2559.4375 -29.2693) 
(list 2559.4375 -30.2693) 
(list 2559.4375 -30.2693) 
(list 2559.7375 -40.2693)))
(apply 'command (append '("pline") coords '("c")))
(setq currobj (ssadd (entlast) currobj))
(command "_layer" "set" "prebias" "")
(setq coords (list 
(list 2559.4375 -40.2693) 
(list 2559.4375 -29.2693) 
(list 2485.415 -30.0193) 
(list 2485.415 -25.0763) 
(list 2559.4375 -25.8263) 
(list 2559.4375 -14.8263) 
(list 2560.5625 -14.8263) 
(list 2560.5625 -25.8263) 
(list 2634.585 -25.0763) 
(list 2634.585 -30.0193) 
(list 2560.5625 -29.2693) 
(list 2560.5625 -40.2693)))
(apply 'command (append '("pline") coords '("c")))
(setq currobj (ssadd (entlast) currobj))
(command "_layer" "set" "nitride" "")
(command "_layer" "set" "fda1" "")
(setq coords (list 
(list 2560.5625 -29.1263) 
(list 2634.585 -29.8763) 
(list 2634.585 -29.6993) 
(list 2560.5625 -29.0493)))
(apply 'command (append '("pline") coords '("c")))
(setq currobj (ssadd (entlast) currobj))
(setq coords (list 
(list 2560.5625 -28.9063) 
(list 2634.585 -29.5563) 
(list 2634.585 -29.3793) 
(list 2560.5625 -28.8293)))
(apply 'command (append '("pline") coords '("c")))
(setq currobj (ssadd (entlast) currobj))
(setq coords (list 
(list 2560.5625 -28.6863) 
(list 2634.585 -29.2363) 
(list 2634.585 -29.0593) 
(list 2560.5625 -28.6093)))
(apply 'command (append '("pline") coords '("c")))
(setq currobj (ssadd (entlast) currobj))
(setq coords (list 
(list 2560.5625 -28.4663) 
(list 2634.585 -28.9163) 
(list 2634.585 -28.7393) 
(list 2560.5625 -28.3893)))
(apply 'command (append '("pline") coords '("c")))
(setq currobj (ssadd (entlast) currobj))
(setq coords (list 
(list 2560.5625 -28.2463) 
(list 2634.585 -28.5963) 
(list 2634.585 -28.4193) 
(list 2560.5625 -28.1693)))
(apply 'command (append '("pline") coords '("c")))
(setq currobj (ssadd (entlast) currobj))
(setq coords (list 
(list 2560.5625 -28.0263) 
(list 2634.585 -28.2763) 
(list 2634.585 -28.0993) 
(list 2560.5625 -27.9493)))
(apply 'command (append '("pline") coords '("c")))
(setq currobj (ssadd (entlast) currobj))
(setq coords (list 
(list 2560.5625 -27.8063) 
(list 2634.585 -27.9563) 
(list 2634.585 -27.7793) 
(list 2560.5625 -27.7293)))
(apply 'command (append '("pline") coords '("c")))
(setq currobj (ssadd (entlast) currobj))
(setq coords (list 
(list 2560.5625 -27.5863) 
(list 2634.585 -27.6363) 
(list 2634.585 -27.4593) 
(list 2560.5625 -27.5093)))
(apply 'command (append '("pline") coords '("c")))
(setq currobj (ssadd (entlast) currobj))
(setq coords (list 
(list 2560.5625 -27.3663) 
(list 2634.585 -27.3163) 
(list 2634.585 -27.1393) 
(list 2560.5625 -27.2893)))
(apply 'command (append '("pline") coords '("c")))
(setq currobj (ssadd (entlast) currobj))
(setq coords (list 
(list 2560.5625 -27.1463) 
(list 2634.585 -26.9963) 
(list 2634.585 -26.8193) 
(list 2560.5625 -27.0693)))
(apply 'command (append '("pline") coords '("c")))
(setq currobj (ssadd (entlast) currobj))
(setq coords (list 
(list 2560.5625 -26.9263) 
(list 2634.585 -26.6763) 
(list 2634.585 -26.4993) 
(list 2560.5625 -26.8493)))
(apply 'command (append '("pline") coords '("c")))
(setq currobj (ssadd (entlast) currobj))
(setq coords (list 
(list 2560.5625 -26.7063) 
(list 2634.585 -26.3563) 
(list 2634.585 -26.1793) 
(list 2560.5625 -26.6293)))
(apply 'command (append '("pline") coords '("c")))
(setq currobj (ssadd (entlast) currobj))
(setq coords (list 
(list 2560.5625 -26.4863) 
(list 2634.585 -26.0363) 
(list 2634.585 -25.8593) 
(list 2560.5625 -26.4093)))
(apply 'command (append '("pline") coords '("c")))
(setq currobj (ssadd (entlast) currobj))
(setq coords (list 
(list 2560.5625 -26.2663) 
(list 2634.585 -25.7163) 
(list 2634.585 -25.5393) 
(list 2560.5625 -26.1893)))
(apply 'command (append '("pline") coords '("c")))
(setq currobj (ssadd (entlast) currobj))
(setq coords (list 
(list 2560.5625 -26.0463) 
(list 2634.585 -25.3963) 
(list 2634.585 -25.2193) 
(list 2560.5625 -25.9693)))
(apply 'command (append '("pline") coords '("c")))
(setq currobj (ssadd (entlast) currobj))
(setq coords (list 
(list 2559.4375 -25.9693) 
(list 2485.415 -25.2193) 
(list 2485.415 -25.3963) 
(list 2559.4375 -26.0463)))
(apply 'command (append '("pline") coords '("c")))
(setq currobj (ssadd (entlast) currobj))
(setq coords (list 
(list 2559.4375 -26.1893) 
(list 2485.415 -25.5393) 
(list 2485.415 -25.7163) 
(list 2559.4375 -26.2663)))
(apply 'command (append '("pline") coords '("c")))
(setq currobj (ssadd (entlast) currobj))
(setq coords (list 
(list 2559.4375 -26.4093) 
(list 2485.415 -25.8593) 
(list 2485.415 -26.0363) 
(list 2559.4375 -26.4863)))
(apply 'command (append '("pline") coords '("c")))
(setq currobj (ssadd (entlast) currobj))
(setq coords (list 
(list 2559.4375 -26.6293) 
(list 2485.415 -26.1793) 
(list 2485.415 -26.3563) 
(list 2559.4375 -26.7063)))
(apply 'command (append '("pline") coords '("c")))
(setq currobj (ssadd (entlast) currobj))
(setq coords (list 
(list 2559.4375 -26.8493) 
(list 2485.415 -26.4993) 
(list 2485.415 -26.6763) 
(list 2559.4375 -26.9263)))
(apply 'command (append '("pline") coords '("c")))
(setq currobj (ssadd (entlast) currobj))
(setq coords (list 
(list 2559.4375 -27.0693) 
(list 2485.415 -26.8193) 
(list 2485.415 -26.9963) 
(list 2559.4375 -27.1463)))
(apply 'command (append '("pline") coords '("c")))
(setq currobj (ssadd (entlast) currobj))
(setq coords (list 
(list 2559.4375 -27.2893) 
(list 2485.415 -27.1393) 
(list 2485.415 -27.3163) 
(list 2559.4375 -27.3663)))
(apply 'command (append '("pline") coords '("c")))
(setq currobj (ssadd (entlast) currobj))
(setq coords (list 
(list 2559.4375 -27.5093) 
(list 2485.415 -27.4593) 
(list 2485.415 -27.6363) 
(list 2559.4375 -27.5863)))
(apply 'command (append '("pline") coords '("c")))
(setq currobj (ssadd (entlast) currobj))
(setq coords (list 
(list 2559.4375 -27.7293) 
(list 2485.415 -27.7793) 
(list 2485.415 -27.9563) 
(list 2559.4375 -27.8063)))
(apply 'command (append '("pline") coords '("c")))
(setq currobj (ssadd (entlast) currobj))
(setq coords (list 
(list 2559.4375 -27.9493) 
(list 2485.415 -28.0993) 
(list 2485.415 -28.2763) 
(list 2559.4375 -28.0263)))
(apply 'command (append '("pline") coords '("c")))
(setq currobj (ssadd (entlast) currobj))
(setq coords (list 
(list 2559.4375 -28.1693) 
(list 2485.415 -28.4193) 
(list 2485.415 -28.5963) 
(list 2559.4375 -28.2463)))
(apply 'command (append '("pline") coords '("c")))
(setq currobj (ssadd (entlast) currobj))
(setq coords (list 
(list 2559.4375 -28.3893) 
(list 2485.415 -28.7393) 
(list 2485.415 -28.9163) 
(list 2559.4375 -28.4663)))
(apply 'command (append '("pline") coords '("c")))
(setq currobj (ssadd (entlast) currobj))
(setq coords (list 
(list 2559.4375 -28.6093) 
(list 2485.415 -29.0593) 
(list 2485.415 -29.2363) 
(list 2559.4375 -28.6863)))
(apply 'command (append '("pline") coords '("c")))
(setq currobj (ssadd (entlast) currobj))
(setq coords (list 
(list 2559.4375 -28.8293) 
(list 2485.415 -29.3793) 
(list 2485.415 -29.5563) 
(list 2559.4375 -28.9063)))
(apply 'command (append '("pline") coords '("c")))
(setq currobj (ssadd (entlast) currobj))
(setq coords (list 
(list 2559.4375 -29.0493) 
(list 2485.415 -29.6993) 
(list 2485.415 -29.8763) 
(list 2559.4375 -29.1263)))
(apply 'command (append '("pline") coords '("c")))
(setq currobj (ssadd (entlast) currobj))
(command "_layer" "set" "nitride" "")
(command "_layer" "set" "text" "")
(command "_circle" "2559.0625,-40.2693" "0.075")
(command "_circle" "2559.0625,-39.9693" "0.075")
(command "_circle" "2559.0625,-39.6693" "0.075")
(command "_circle" "2559.0625,-39.3693" "0.075")
(command "_circle" "2559.0625,-39.0693" "0.075")
(command "_circle" "2558.7625,-40.2693" "0.075")
(command "_circle" "2558.7625,-39.9693" "0.075")
(command "_circle" "2558.7625,-39.6693" "0.075")
(command "_circle" "2558.7625,-39.3693" "0.075")
(command "_circle" "2558.7625,-39.0693" "0.075")
(command "_circle" "2558.4625,-40.2693" "0.075")
(command "_circle" "2558.4625,-39.9693" "0.075")
(command "_circle" "2558.4625,-39.6693" "0.075")
(command "_circle" "2558.4625,-39.3693" "0.075")
(command "_circle" "2558.4625,-39.0693" "0.075")
(command "_circle" "2558.1625,-40.2693" "0.075")
(command "_circle" "2558.1625,-39.9693" "0.075")
(command "_circle" "2558.1625,-39.6693" "0.075")
(command "_circle" "2558.1625,-39.3693" "0.075")
(command "_circle" "2558.1625,-39.0693" "0.075")
(command "_circle" "2557.8625,-40.2693" "0.075")
(command "_circle" "2557.8625,-39.9693" "0.075")
(command "_circle" "2557.8625,-39.6693" "0.075")
(command "_circle" "2557.8625,-39.3693" "0.075")
(command "_circle" "2557.8625,-39.0693" "0.075")
(command "_layer" "set" "nitride" "")
(setq coords (list 
(list 2560.2625 -14.8263) 
(list 2560.2625 100.8184) 
(list 2559.7375 100.8184) 
(list 2559.7375 -14.8263)))
(apply 'command (append '("pline") coords '("c")))
(setq currobj (ssadd (entlast) currobj))
(command "_layer" "set" "prebias" "")
(command "_rectangle" "2559.7375,-14.8263" "2560.2625,100.8184")
(setq currobj (ssadd (entlast) currobj))
(command "_layer" "set" "nitride" "")
(setq coords (list 
(list 2560.2625 100.8184) 
(list 2560.5625 110.8184) 
(list 2560.5625 110.8184) 
(list 2560.5625 111.8184) 
(list 2634.585 111.0684) 
(list 2634.585 116.0114) 
(list 2560.5625 115.2614) 
(list 2560.5625 116.2614) 
(list 2560.5625 116.2614) 
(list 2560.2625 126.2614) 
(list 2559.7375 126.2614) 
(list 2559.4375 116.2614) 
(list 2559.4375 116.2614) 
(list 2559.4375 115.2614) 
(list 2485.415 116.0114) 
(list 2485.415 111.0684) 
(list 2559.4375 111.8184) 
(list 2559.4375 110.8184) 
(list 2559.4375 110.8184) 
(list 2559.7375 100.8184)))
(apply 'command (append '("pline") coords '("c")))
(setq currobj (ssadd (entlast) currobj))
(command "_layer" "set" "prebias" "")
(setq coords (list 
(list 2559.4375 100.8184) 
(list 2559.4375 111.8184) 
(list 2485.415 111.0684) 
(list 2485.415 116.0114) 
(list 2559.4375 115.2614) 
(list 2559.4375 126.2614) 
(list 2560.5625 126.2614) 
(list 2560.5625 115.2614) 
(list 2634.585 116.0114) 
(list 2634.585 111.0684) 
(list 2560.5625 111.8184) 
(list 2560.5625 100.8184)))
(apply 'command (append '("pline") coords '("c")))
(setq currobj (ssadd (entlast) currobj))
(command "_layer" "set" "nitride" "")
(command "_layer" "set" "fda1" "")
(setq coords (list 
(list 2560.5625 111.9614) 
(list 2634.585 111.2114) 
(list 2634.585 111.3884) 
(list 2560.5625 112.0384)))
(apply 'command (append '("pline") coords '("c")))
(setq currobj (ssadd (entlast) currobj))
(setq coords (list 
(list 2560.5625 112.1814) 
(list 2634.585 111.5314) 
(list 2634.585 111.7084) 
(list 2560.5625 112.2584)))
(apply 'command (append '("pline") coords '("c")))
(setq currobj (ssadd (entlast) currobj))
(setq coords (list 
(list 2560.5625 112.4014) 
(list 2634.585 111.8514) 
(list 2634.585 112.0284) 
(list 2560.5625 112.4784)))
(apply 'command (append '("pline") coords '("c")))
(setq currobj (ssadd (entlast) currobj))
(setq coords (list 
(list 2560.5625 112.6214) 
(list 2634.585 112.1714) 
(list 2634.585 112.3484) 
(list 2560.5625 112.6984)))
(apply 'command (append '("pline") coords '("c")))
(setq currobj (ssadd (entlast) currobj))
(setq coords (list 
(list 2560.5625 112.8414) 
(list 2634.585 112.4914) 
(list 2634.585 112.6684) 
(list 2560.5625 112.9184)))
(apply 'command (append '("pline") coords '("c")))
(setq currobj (ssadd (entlast) currobj))
(setq coords (list 
(list 2560.5625 113.0614) 
(list 2634.585 112.8114) 
(list 2634.585 112.9884) 
(list 2560.5625 113.1384)))
(apply 'command (append '("pline") coords '("c")))
(setq currobj (ssadd (entlast) currobj))
(setq coords (list 
(list 2560.5625 113.2814) 
(list 2634.585 113.1314) 
(list 2634.585 113.3084) 
(list 2560.5625 113.3584)))
(apply 'command (append '("pline") coords '("c")))
(setq currobj (ssadd (entlast) currobj))
(setq coords (list 
(list 2560.5625 113.5014) 
(list 2634.585 113.4514) 
(list 2634.585 113.6284) 
(list 2560.5625 113.5784)))
(apply 'command (append '("pline") coords '("c")))
(setq currobj (ssadd (entlast) currobj))
(setq coords (list 
(list 2560.5625 113.7214) 
(list 2634.585 113.7714) 
(list 2634.585 113.9484) 
(list 2560.5625 113.7984)))
(apply 'command (append '("pline") coords '("c")))
(setq currobj (ssadd (entlast) currobj))
(setq coords (list 
(list 2560.5625 113.9414) 
(list 2634.585 114.0914) 
(list 2634.585 114.2684) 
(list 2560.5625 114.0184)))
(apply 'command (append '("pline") coords '("c")))
(setq currobj (ssadd (entlast) currobj))
(setq coords (list 
(list 2560.5625 114.1614) 
(list 2634.585 114.4114) 
(list 2634.585 114.5884) 
(list 2560.5625 114.2384)))
(apply 'command (append '("pline") coords '("c")))
(setq currobj (ssadd (entlast) currobj))
(setq coords (list 
(list 2560.5625 114.3814) 
(list 2634.585 114.7314) 
(list 2634.585 114.9084) 
(list 2560.5625 114.4584)))
(apply 'command (append '("pline") coords '("c")))
(setq currobj (ssadd (entlast) currobj))
(setq coords (list 
(list 2560.5625 114.6014) 
(list 2634.585 115.0514) 
(list 2634.585 115.2284) 
(list 2560.5625 114.6784)))
(apply 'command (append '("pline") coords '("c")))
(setq currobj (ssadd (entlast) currobj))
(setq coords (list 
(list 2560.5625 114.8214) 
(list 2634.585 115.3714) 
(list 2634.585 115.5484) 
(list 2560.5625 114.8984)))
(apply 'command (append '("pline") coords '("c")))
(setq currobj (ssadd (entlast) currobj))
(setq coords (list 
(list 2560.5625 115.0414) 
(list 2634.585 115.6914) 
(list 2634.585 115.8684) 
(list 2560.5625 115.1184)))
(apply 'command (append '("pline") coords '("c")))
(setq currobj (ssadd (entlast) currobj))
(setq coords (list 
(list 2559.4375 115.1184) 
(list 2485.415 115.8684) 
(list 2485.415 115.6914) 
(list 2559.4375 115.0414)))
(apply 'command (append '("pline") coords '("c")))
(setq currobj (ssadd (entlast) currobj))
(setq coords (list 
(list 2559.4375 114.8984) 
(list 2485.415 115.5484) 
(list 2485.415 115.3714) 
(list 2559.4375 114.8214)))
(apply 'command (append '("pline") coords '("c")))
(setq currobj (ssadd (entlast) currobj))
(setq coords (list 
(list 2559.4375 114.6784) 
(list 2485.415 115.2284) 
(list 2485.415 115.0514) 
(list 2559.4375 114.6014)))
(apply 'command (append '("pline") coords '("c")))
(setq currobj (ssadd (entlast) currobj))
(setq coords (list 
(list 2559.4375 114.4584) 
(list 2485.415 114.9084) 
(list 2485.415 114.7314) 
(list 2559.4375 114.3814)))
(apply 'command (append '("pline") coords '("c")))
(setq currobj (ssadd (entlast) currobj))
(setq coords (list 
(list 2559.4375 114.2384) 
(list 2485.415 114.5884) 
(list 2485.415 114.4114) 
(list 2559.4375 114.1614)))
(apply 'command (append '("pline") coords '("c")))
(setq currobj (ssadd (entlast) currobj))
(setq coords (list 
(list 2559.4375 114.0184) 
(list 2485.415 114.2684) 
(list 2485.415 114.0914) 
(list 2559.4375 113.9414)))
(apply 'command (append '("pline") coords '("c")))
(setq currobj (ssadd (entlast) currobj))
(setq coords (list 
(list 2559.4375 113.7984) 
(list 2485.415 113.9484) 
(list 2485.415 113.7714) 
(list 2559.4375 113.7214)))
(apply 'command (append '("pline") coords '("c")))
(setq currobj (ssadd (entlast) currobj))
(setq coords (list 
(list 2559.4375 113.5784) 
(list 2485.415 113.6284) 
(list 2485.415 113.4514) 
(list 2559.4375 113.5014)))
(apply 'command (append '("pline") coords '("c")))
(setq currobj (ssadd (entlast) currobj))
(setq coords (list 
(list 2559.4375 113.3584) 
(list 2485.415 113.3084) 
(list 2485.415 113.1314) 
(list 2559.4375 113.2814)))
(apply 'command (append '("pline") coords '("c")))
(setq currobj (ssadd (entlast) currobj))
(setq coords (list 
(list 2559.4375 113.1384) 
(list 2485.415 112.9884) 
(list 2485.415 112.8114) 
(list 2559.4375 113.0614)))
(apply 'command (append '("pline") coords '("c")))
(setq currobj (ssadd (entlast) currobj))
(setq coords (list 
(list 2559.4375 112.9184) 
(list 2485.415 112.6684) 
(list 2485.415 112.4914) 
(list 2559.4375 112.8414)))
(apply 'command (append '("pline") coords '("c")))
(setq currobj (ssadd (entlast) currobj))
(setq coords (list 
(list 2559.4375 112.6984) 
(list 2485.415 112.3484) 
(list 2485.415 112.1714) 
(list 2559.4375 112.6214)))
(apply 'command (append '("pline") coords '("c")))
(setq currobj (ssadd (entlast) currobj))
(setq coords (list 
(list 2559.4375 112.4784) 
(list 2485.415 112.0284) 
(list 2485.415 111.8514) 
(list 2559.4375 112.4014)))
(apply 'command (append '("pline") coords '("c")))
(setq currobj (ssadd (entlast) currobj))
(setq coords (list 
(list 2559.4375 112.2584) 
(list 2485.415 111.7084) 
(list 2485.415 111.5314) 
(list 2559.4375 112.1814)))
(apply 'command (append '("pline") coords '("c")))
(setq currobj (ssadd (entlast) currobj))
(setq coords (list 
(list 2559.4375 112.0384) 
(list 2485.415 111.3884) 
(list 2485.415 111.2114) 
(list 2559.4375 111.9614)))
(apply 'command (append '("pline") coords '("c")))
(setq currobj (ssadd (entlast) currobj))
(command "_layer" "set" "nitride" "")
(command "_layer" "set" "text" "")
(command "_circle" "2559.0625,100.8184" "0.075")
(command "_circle" "2559.0625,101.1184" "0.075")
(command "_circle" "2559.0625,101.4184" "0.075")
(command "_circle" "2559.0625,101.7184" "0.075")
(command "_circle" "2559.0625,102.0184" "0.075")
(command "_circle" "2558.7625,100.8184" "0.075")
(command "_circle" "2558.7625,101.1184" "0.075")
(command "_circle" "2558.7625,101.4184" "0.075")
(command "_circle" "2558.7625,101.7184" "0.075")
(command "_circle" "2558.7625,102.0184" "0.075")
(command "_circle" "2558.4625,100.8184" "0.075")
(command "_circle" "2558.4625,101.1184" "0.075")
(command "_circle" "2558.4625,101.4184" "0.075")
(command "_circle" "2558.4625,101.7184" "0.075")
(command "_circle" "2558.4625,102.0184" "0.075")
(command "_circle" "2558.1625,100.8184" "0.075")
(command "_circle" "2558.1625,101.1184" "0.075")
(command "_circle" "2558.1625,101.4184" "0.075")
(command "_circle" "2558.1625,101.7184" "0.075")
(command "_circle" "2558.1625,102.0184" "0.075")
(command "_circle" "2557.8625,100.8184" "0.075")
(command "_circle" "2557.8625,101.1184" "0.075")
(command "_circle" "2557.8625,101.4184" "0.075")
(command "_circle" "2557.8625,101.7184" "0.075")
(command "_circle" "2557.8625,102.0184" "0.075")
(command "_layer" "set" "nitride" "")
(setq coords (list 
(list 2560.2625 126.2614) 
(list 2560.2625 241.9061) 
(list 2559.7375 241.9061) 
(list 2559.7375 126.2614)))
(apply 'command (append '("pline") coords '("c")))
(setq currobj (ssadd (entlast) currobj))
(command "_layer" "set" "prebias" "")
(command "_rectangle" "2559.7375,126.2614" "2560.2625,241.9061")
(setq currobj (ssadd (entlast) currobj))
(command "_layer" "set" "nitride" "")
(setq coords (list 
(list 2560.2625 241.9061) 
(list 2560.5625 251.9061) 
(list 2560.5625 251.9061) 
(list 2560.5625 252.9061) 
(list 2634.585 252.1561) 
(list 2634.585 257.0991) 
(list 2560.5625 256.3491) 
(list 2560.5625 257.3491) 
(list 2560.5625 257.3491) 
(list 2560.2625 267.3491) 
(list 2559.7375 267.3491) 
(list 2559.4375 257.3491) 
(list 2559.4375 257.3491) 
(list 2559.4375 256.3491) 
(list 2485.415 257.0991) 
(list 2485.415 252.1561) 
(list 2559.4375 252.9061) 
(list 2559.4375 251.9061) 
(list 2559.4375 251.9061) 
(list 2559.7375 241.9061)))
(apply 'command (append '("pline") coords '("c")))
(setq currobj (ssadd (entlast) currobj))
(command "_layer" "set" "prebias" "")
(setq coords (list 
(list 2559.4375 241.9061) 
(list 2559.4375 252.9061) 
(list 2485.415 252.1561) 
(list 2485.415 257.0991) 
(list 2559.4375 256.3491) 
(list 2559.4375 267.3491) 
(list 2560.5625 267.3491) 
(list 2560.5625 256.3491) 
(list 2634.585 257.0991) 
(list 2634.585 252.1561) 
(list 2560.5625 252.9061) 
(list 2560.5625 241.9061)))
(apply 'command (append '("pline") coords '("c")))
(setq currobj (ssadd (entlast) currobj))
(command "_layer" "set" "nitride" "")
(command "_layer" "set" "fda1" "")
(setq coords (list 
(list 2560.5625 253.0491) 
(list 2634.585 252.2991) 
(list 2634.585 252.4761) 
(list 2560.5625 253.1261)))
(apply 'command (append '("pline") coords '("c")))
(setq currobj (ssadd (entlast) currobj))
(setq coords (list 
(list 2560.5625 253.2691) 
(list 2634.585 252.6191) 
(list 2634.585 252.7961) 
(list 2560.5625 253.3461)))
(apply 'command (append '("pline") coords '("c")))
(setq currobj (ssadd (entlast) currobj))
(setq coords (list 
(list 2560.5625 253.4891) 
(list 2634.585 252.9391) 
(list 2634.585 253.1161) 
(list 2560.5625 253.5661)))
(apply 'command (append '("pline") coords '("c")))
(setq currobj (ssadd (entlast) currobj))
(setq coords (list 
(list 2560.5625 253.7091) 
(list 2634.585 253.2591) 
(list 2634.585 253.4361) 
(list 2560.5625 253.7861)))
(apply 'command (append '("pline") coords '("c")))
(setq currobj (ssadd (entlast) currobj))
(setq coords (list 
(list 2560.5625 253.9291) 
(list 2634.585 253.5791) 
(list 2634.585 253.7561) 
(list 2560.5625 254.0061)))
(apply 'command (append '("pline") coords '("c")))
(setq currobj (ssadd (entlast) currobj))
(setq coords (list 
(list 2560.5625 254.1491) 
(list 2634.585 253.8991) 
(list 2634.585 254.0761) 
(list 2560.5625 254.2261)))
(apply 'command (append '("pline") coords '("c")))
(setq currobj (ssadd (entlast) currobj))
(setq coords (list 
(list 2560.5625 254.3691) 
(list 2634.585 254.2191) 
(list 2634.585 254.3961) 
(list 2560.5625 254.4461)))
(apply 'command (append '("pline") coords '("c")))
(setq currobj (ssadd (entlast) currobj))
(setq coords (list 
(list 2560.5625 254.5891) 
(list 2634.585 254.5391) 
(list 2634.585 254.7161) 
(list 2560.5625 254.6661)))
(apply 'command (append '("pline") coords '("c")))
(setq currobj (ssadd (entlast) currobj))
(setq coords (list 
(list 2560.5625 254.8091) 
(list 2634.585 254.8591) 
(list 2634.585 255.0361) 
(list 2560.5625 254.8861)))
(apply 'command (append '("pline") coords '("c")))
(setq currobj (ssadd (entlast) currobj))
(setq coords (list 
(list 2560.5625 255.0291) 
(list 2634.585 255.1791) 
(list 2634.585 255.3561) 
(list 2560.5625 255.1061)))
(apply 'command (append '("pline") coords '("c")))
(setq currobj (ssadd (entlast) currobj))
(setq coords (list 
(list 2560.5625 255.2491) 
(list 2634.585 255.4991) 
(list 2634.585 255.6761) 
(list 2560.5625 255.3261)))
(apply 'command (append '("pline") coords '("c")))
(setq currobj (ssadd (entlast) currobj))
(setq coords (list 
(list 2560.5625 255.4691) 
(list 2634.585 255.8191) 
(list 2634.585 255.9961) 
(list 2560.5625 255.5461)))
(apply 'command (append '("pline") coords '("c")))
(setq currobj (ssadd (entlast) currobj))
(setq coords (list 
(list 2560.5625 255.6891) 
(list 2634.585 256.1391) 
(list 2634.585 256.3161) 
(list 2560.5625 255.7661)))
(apply 'command (append '("pline") coords '("c")))
(setq currobj (ssadd (entlast) currobj))
(setq coords (list 
(list 2560.5625 255.9091) 
(list 2634.585 256.4591) 
(list 2634.585 256.6361) 
(list 2560.5625 255.9861)))
(apply 'command (append '("pline") coords '("c")))
(setq currobj (ssadd (entlast) currobj))
(setq coords (list 
(list 2560.5625 256.1291) 
(list 2634.585 256.7791) 
(list 2634.585 256.9561) 
(list 2560.5625 256.2061)))
(apply 'command (append '("pline") coords '("c")))
(setq currobj (ssadd (entlast) currobj))
(setq coords (list 
(list 2559.4375 256.2061) 
(list 2485.415 256.9561) 
(list 2485.415 256.7791) 
(list 2559.4375 256.1291)))
(apply 'command (append '("pline") coords '("c")))
(setq currobj (ssadd (entlast) currobj))
(setq coords (list 
(list 2559.4375 255.9861) 
(list 2485.415 256.6361) 
(list 2485.415 256.4591) 
(list 2559.4375 255.9091)))
(apply 'command (append '("pline") coords '("c")))
(setq currobj (ssadd (entlast) currobj))
(setq coords (list 
(list 2559.4375 255.7661) 
(list 2485.415 256.3161) 
(list 2485.415 256.1391) 
(list 2559.4375 255.6891)))
(apply 'command (append '("pline") coords '("c")))
(setq currobj (ssadd (entlast) currobj))
(setq coords (list 
(list 2559.4375 255.5461) 
(list 2485.415 255.9961) 
(list 2485.415 255.8191) 
(list 2559.4375 255.4691)))
(apply 'command (append '("pline") coords '("c")))
(setq currobj (ssadd (entlast) currobj))
(setq coords (list 
(list 2559.4375 255.3261) 
(list 2485.415 255.6761) 
(list 2485.415 255.4991) 
(list 2559.4375 255.2491)))
(apply 'command (append '("pline") coords '("c")))
(setq currobj (ssadd (entlast) currobj))
(setq coords (list 
(list 2559.4375 255.1061) 
(list 2485.415 255.3561) 
(list 2485.415 255.1791) 
(list 2559.4375 255.0291)))
(apply 'command (append '("pline") coords '("c")))
(setq currobj (ssadd (entlast) currobj))
(setq coords (list 
(list 2559.4375 254.8861) 
(list 2485.415 255.0361) 
(list 2485.415 254.8591) 
(list 2559.4375 254.8091)))
(apply 'command (append '("pline") coords '("c")))
(setq currobj (ssadd (entlast) currobj))
(setq coords (list 
(list 2559.4375 254.6661) 
(list 2485.415 254.7161) 
(list 2485.415 254.5391) 
(list 2559.4375 254.5891)))
(apply 'command (append '("pline") coords '("c")))
(setq currobj (ssadd (entlast) currobj))
(setq coords (list 
(list 2559.4375 254.4461) 
(list 2485.415 254.3961) 
(list 2485.415 254.2191) 
(list 2559.4375 254.3691)))
(apply 'command (append '("pline") coords '("c")))
(setq currobj (ssadd (entlast) currobj))
(setq coords (list 
(list 2559.4375 254.2261) 
(list 2485.415 254.0761) 
(list 2485.415 253.8991) 
(list 2559.4375 254.1491)))
(apply 'command (append '("pline") coords '("c")))
(setq currobj (ssadd (entlast) currobj))
(setq coords (list 
(list 2559.4375 254.0061) 
(list 2485.415 253.7561) 
(list 2485.415 253.5791) 
(list 2559.4375 253.9291)))
(apply 'command (append '("pline") coords '("c")))
(setq currobj (ssadd (entlast) currobj))
(setq coords (list 
(list 2559.4375 253.7861) 
(list 2485.415 253.4361) 
(list 2485.415 253.2591) 
(list 2559.4375 253.7091)))
(apply 'command (append '("pline") coords '("c")))
(setq currobj (ssadd (entlast) currobj))
(setq coords (list 
(list 2559.4375 253.5661) 
(list 2485.415 253.1161) 
(list 2485.415 252.9391) 
(list 2559.4375 253.4891)))
(apply 'command (append '("pline") coords '("c")))
(setq currobj (ssadd (entlast) currobj))
(setq coords (list 
(list 2559.4375 253.3461) 
(list 2485.415 252.7961) 
(list 2485.415 252.6191) 
(list 2559.4375 253.2691)))
(apply 'command (append '("pline") coords '("c")))
(setq currobj (ssadd (entlast) currobj))
(setq coords (list 
(list 2559.4375 253.1261) 
(list 2485.415 252.4761) 
(list 2485.415 252.2991) 
(list 2559.4375 253.0491)))
(apply 'command (append '("pline") coords '("c")))
(setq currobj (ssadd (entlast) currobj))
(command "_layer" "set" "nitride" "")
(command "_layer" "set" "text" "")
(command "_circle" "2559.0625,241.9061" "0.075")
(command "_circle" "2559.0625,242.2061" "0.075")
(command "_circle" "2559.0625,242.5061" "0.075")
(command "_circle" "2559.0625,242.8061" "0.075")
(command "_circle" "2559.0625,243.1061" "0.075")
(command "_circle" "2558.7625,241.9061" "0.075")
(command "_circle" "2558.7625,242.2061" "0.075")
(command "_circle" "2558.7625,242.5061" "0.075")
(command "_circle" "2558.7625,242.8061" "0.075")
(command "_circle" "2558.7625,243.1061" "0.075")
(command "_circle" "2558.4625,241.9061" "0.075")
(command "_circle" "2558.4625,242.2061" "0.075")
(command "_circle" "2558.4625,242.5061" "0.075")
(command "_circle" "2558.4625,242.8061" "0.075")
(command "_circle" "2558.4625,243.1061" "0.075")
(command "_circle" "2558.1625,241.9061" "0.075")
(command "_circle" "2558.1625,242.2061" "0.075")
(command "_circle" "2558.1625,242.5061" "0.075")
(command "_circle" "2558.1625,242.8061" "0.075")
(command "_circle" "2558.1625,243.1061" "0.075")
(command "_circle" "2557.8625,241.9061" "0.075")
(command "_circle" "2557.8625,242.2061" "0.075")
(command "_circle" "2557.8625,242.5061" "0.075")
(command "_circle" "2557.8625,242.8061" "0.075")
(command "_circle" "2557.8625,243.1061" "0.075")
(command "_layer" "set" "nitride" "")
(setq coords (list 
(list 2560.2625 267.3491) 
(list 2560.2625 382.9939) 
(list 2559.7375 382.9939) 
(list 2559.7375 267.3491)))
(apply 'command (append '("pline") coords '("c")))
(setq currobj (ssadd (entlast) currobj))
(command "_layer" "set" "prebias" "")
(command "_rectangle" "2559.7375,267.3491" "2560.2625,382.9939")
(setq currobj (ssadd (entlast) currobj))
(command "_layer" "set" "nitride" "")
(setq coords (list 
(list 2560.2625 382.9939) 
(list 2560.5625 392.9939) 
(list 2560.5625 392.9939) 
(list 2560.5625 393.9939) 
(list 2634.585 393.2439) 
(list 2634.585 398.1869) 
(list 2560.5625 397.4369) 
(list 2560.5625 398.4369) 
(list 2560.5625 398.4369) 
(list 2560.2625 408.4369) 
(list 2559.7375 408.4369) 
(list 2559.4375 398.4369) 
(list 2559.4375 398.4369) 
(list 2559.4375 397.4369) 
(list 2485.415 398.1869) 
(list 2485.415 393.2439) 
(list 2559.4375 393.9939) 
(list 2559.4375 392.9939) 
(list 2559.4375 392.9939) 
(list 2559.7375 382.9939)))
(apply 'command (append '("pline") coords '("c")))
(setq currobj (ssadd (entlast) currobj))
(command "_layer" "set" "prebias" "")
(setq coords (list 
(list 2559.4375 382.9939) 
(list 2559.4375 393.9939) 
(list 2485.415 393.2439) 
(list 2485.415 398.1869) 
(list 2559.4375 397.4369) 
(list 2559.4375 408.4369) 
(list 2560.5625 408.4369) 
(list 2560.5625 397.4369) 
(list 2634.585 398.1869) 
(list 2634.585 393.2439) 
(list 2560.5625 393.9939) 
(list 2560.5625 382.9939)))
(apply 'command (append '("pline") coords '("c")))
(setq currobj (ssadd (entlast) currobj))
(command "_layer" "set" "nitride" "")
(command "_layer" "set" "fda1" "")
(setq coords (list 
(list 2560.5625 394.1369) 
(list 2634.585 393.3869) 
(list 2634.585 393.5639) 
(list 2560.5625 394.2139)))
(apply 'command (append '("pline") coords '("c")))
(setq currobj (ssadd (entlast) currobj))
(setq coords (list 
(list 2560.5625 394.3569) 
(list 2634.585 393.7069) 
(list 2634.585 393.8839) 
(list 2560.5625 394.4339)))
(apply 'command (append '("pline") coords '("c")))
(setq currobj (ssadd (entlast) currobj))
(setq coords (list 
(list 2560.5625 394.5769) 
(list 2634.585 394.0269) 
(list 2634.585 394.2039) 
(list 2560.5625 394.6539)))
(apply 'command (append '("pline") coords '("c")))
(setq currobj (ssadd (entlast) currobj))
(setq coords (list 
(list 2560.5625 394.7969) 
(list 2634.585 394.3469) 
(list 2634.585 394.5239) 
(list 2560.5625 394.8739)))
(apply 'command (append '("pline") coords '("c")))
(setq currobj (ssadd (entlast) currobj))
(setq coords (list 
(list 2560.5625 395.0169) 
(list 2634.585 394.6669) 
(list 2634.585 394.8439) 
(list 2560.5625 395.0939)))
(apply 'command (append '("pline") coords '("c")))
(setq currobj (ssadd (entlast) currobj))
(setq coords (list 
(list 2560.5625 395.2369) 
(list 2634.585 394.9869) 
(list 2634.585 395.1639) 
(list 2560.5625 395.3139)))
(apply 'command (append '("pline") coords '("c")))
(setq currobj (ssadd (entlast) currobj))
(setq coords (list 
(list 2560.5625 395.4569) 
(list 2634.585 395.3069) 
(list 2634.585 395.4839) 
(list 2560.5625 395.5339)))
(apply 'command (append '("pline") coords '("c")))
(setq currobj (ssadd (entlast) currobj))
(setq coords (list 
(list 2560.5625 395.6769) 
(list 2634.585 395.6269) 
(list 2634.585 395.8039) 
(list 2560.5625 395.7539)))
(apply 'command (append '("pline") coords '("c")))
(setq currobj (ssadd (entlast) currobj))
(setq coords (list 
(list 2560.5625 395.8969) 
(list 2634.585 395.9469) 
(list 2634.585 396.1239) 
(list 2560.5625 395.9739)))
(apply 'command (append '("pline") coords '("c")))
(setq currobj (ssadd (entlast) currobj))
(setq coords (list 
(list 2560.5625 396.1169) 
(list 2634.585 396.2669) 
(list 2634.585 396.4439) 
(list 2560.5625 396.1939)))
(apply 'command (append '("pline") coords '("c")))
(setq currobj (ssadd (entlast) currobj))
(setq coords (list 
(list 2560.5625 396.3369) 
(list 2634.585 396.5869) 
(list 2634.585 396.7639) 
(list 2560.5625 396.4139)))
(apply 'command (append '("pline") coords '("c")))
(setq currobj (ssadd (entlast) currobj))
(setq coords (list 
(list 2560.5625 396.5569) 
(list 2634.585 396.9069) 
(list 2634.585 397.0839) 
(list 2560.5625 396.6339)))
(apply 'command (append '("pline") coords '("c")))
(setq currobj (ssadd (entlast) currobj))
(setq coords (list 
(list 2560.5625 396.7769) 
(list 2634.585 397.2269) 
(list 2634.585 397.4039) 
(list 2560.5625 396.8539)))
(apply 'command (append '("pline") coords '("c")))
(setq currobj (ssadd (entlast) currobj))
(setq coords (list 
(list 2560.5625 396.9969) 
(list 2634.585 397.5469) 
(list 2634.585 397.7239) 
(list 2560.5625 397.0739)))
(apply 'command (append '("pline") coords '("c")))
(setq currobj (ssadd (entlast) currobj))
(setq coords (list 
(list 2560.5625 397.2169) 
(list 2634.585 397.8669) 
(list 2634.585 398.0439) 
(list 2560.5625 397.2939)))
(apply 'command (append '("pline") coords '("c")))
(setq currobj (ssadd (entlast) currobj))
(setq coords (list 
(list 2559.4375 397.2939) 
(list 2485.415 398.0439) 
(list 2485.415 397.8669) 
(list 2559.4375 397.2169)))
(apply 'command (append '("pline") coords '("c")))
(setq currobj (ssadd (entlast) currobj))
(setq coords (list 
(list 2559.4375 397.0739) 
(list 2485.415 397.7239) 
(list 2485.415 397.5469) 
(list 2559.4375 396.9969)))
(apply 'command (append '("pline") coords '("c")))
(setq currobj (ssadd (entlast) currobj))
(setq coords (list 
(list 2559.4375 396.8539) 
(list 2485.415 397.4039) 
(list 2485.415 397.2269) 
(list 2559.4375 396.7769)))
(apply 'command (append '("pline") coords '("c")))
(setq currobj (ssadd (entlast) currobj))
(setq coords (list 
(list 2559.4375 396.6339) 
(list 2485.415 397.0839) 
(list 2485.415 396.9069) 
(list 2559.4375 396.5569)))
(apply 'command (append '("pline") coords '("c")))
(setq currobj (ssadd (entlast) currobj))
(setq coords (list 
(list 2559.4375 396.4139) 
(list 2485.415 396.7639) 
(list 2485.415 396.5869) 
(list 2559.4375 396.3369)))
(apply 'command (append '("pline") coords '("c")))
(setq currobj (ssadd (entlast) currobj))
(setq coords (list 
(list 2559.4375 396.1939) 
(list 2485.415 396.4439) 
(list 2485.415 396.2669) 
(list 2559.4375 396.1169)))
(apply 'command (append '("pline") coords '("c")))
(setq currobj (ssadd (entlast) currobj))
(setq coords (list 
(list 2559.4375 395.9739) 
(list 2485.415 396.1239) 
(list 2485.415 395.9469) 
(list 2559.4375 395.8969)))
(apply 'command (append '("pline") coords '("c")))
(setq currobj (ssadd (entlast) currobj))
(setq coords (list 
(list 2559.4375 395.7539) 
(list 2485.415 395.8039) 
(list 2485.415 395.6269) 
(list 2559.4375 395.6769)))
(apply 'command (append '("pline") coords '("c")))
(setq currobj (ssadd (entlast) currobj))
(setq coords (list 
(list 2559.4375 395.5339) 
(list 2485.415 395.4839) 
(list 2485.415 395.3069) 
(list 2559.4375 395.4569)))
(apply 'command (append '("pline") coords '("c")))
(setq currobj (ssadd (entlast) currobj))
(setq coords (list 
(list 2559.4375 395.3139) 
(list 2485.415 395.1639) 
(list 2485.415 394.9869) 
(list 2559.4375 395.2369)))
(apply 'command (append '("pline") coords '("c")))
(setq currobj (ssadd (entlast) currobj))
(setq coords (list 
(list 2559.4375 395.0939) 
(list 2485.415 394.8439) 
(list 2485.415 394.6669) 
(list 2559.4375 395.0169)))
(apply 'command (append '("pline") coords '("c")))
(setq currobj (ssadd (entlast) currobj))
(setq coords (list 
(list 2559.4375 394.8739) 
(list 2485.415 394.5239) 
(list 2485.415 394.3469) 
(list 2559.4375 394.7969)))
(apply 'command (append '("pline") coords '("c")))
(setq currobj (ssadd (entlast) currobj))
(setq coords (list 
(list 2559.4375 394.6539) 
(list 2485.415 394.2039) 
(list 2485.415 394.0269) 
(list 2559.4375 394.5769)))
(apply 'command (append '("pline") coords '("c")))
(setq currobj (ssadd (entlast) currobj))
(setq coords (list 
(list 2559.4375 394.4339) 
(list 2485.415 393.8839) 
(list 2485.415 393.7069) 
(list 2559.4375 394.3569)))
(apply 'command (append '("pline") coords '("c")))
(setq currobj (ssadd (entlast) currobj))
(setq coords (list 
(list 2559.4375 394.2139) 
(list 2485.415 393.5639) 
(list 2485.415 393.3869) 
(list 2559.4375 394.1369)))
(apply 'command (append '("pline") coords '("c")))
(setq currobj (ssadd (entlast) currobj))
(command "_layer" "set" "nitride" "")
(command "_layer" "set" "text" "")
(command "_circle" "2559.0625,382.9939" "0.075")
(command "_circle" "2559.0625,383.2939" "0.075")
(command "_circle" "2559.0625,383.5939" "0.075")
(command "_circle" "2559.0625,383.8939" "0.075")
(command "_circle" "2559.0625,384.1939" "0.075")
(command "_circle" "2558.7625,382.9939" "0.075")
(command "_circle" "2558.7625,383.2939" "0.075")
(command "_circle" "2558.7625,383.5939" "0.075")
(command "_circle" "2558.7625,383.8939" "0.075")
(command "_circle" "2558.7625,384.1939" "0.075")
(command "_circle" "2558.4625,382.9939" "0.075")
(command "_circle" "2558.4625,383.2939" "0.075")
(command "_circle" "2558.4625,383.5939" "0.075")
(command "_circle" "2558.4625,383.8939" "0.075")
(command "_circle" "2558.4625,384.1939" "0.075")
(command "_circle" "2558.1625,382.9939" "0.075")
(command "_circle" "2558.1625,383.2939" "0.075")
(command "_circle" "2558.1625,383.5939" "0.075")
(command "_circle" "2558.1625,383.8939" "0.075")
(command "_circle" "2558.1625,384.1939" "0.075")
(command "_circle" "2557.8625,382.9939" "0.075")
(command "_circle" "2557.8625,383.2939" "0.075")
(command "_circle" "2557.8625,383.5939" "0.075")
(command "_circle" "2557.8625,383.8939" "0.075")
(command "_circle" "2557.8625,384.1939" "0.075")
(command "_layer" "set" "nitride" "")
(setq coords (list 
(list 2560.2625 408.4369) 
(list 2560.2625 524.0816) 
(list 2559.7375 524.0816) 
(list 2559.7375 408.4369)))
(apply 'command (append '("pline") coords '("c")))
(setq currobj (ssadd (entlast) currobj))
(command "_layer" "set" "prebias" "")
(command "_rectangle" "2559.7375,408.4369" "2560.2625,524.0816")
(setq currobj (ssadd (entlast) currobj))
(command "_layer" "set" "nitride" "")
(setq coords (list 
(list 2560.2625 524.0816) 
(list 2560.5625 534.0816) 
(list 2560.5625 534.0816) 
(list 2560.5625 535.0816) 
(list 2634.585 534.3316) 
(list 2634.585 539.2746) 
(list 2560.5625 538.5246) 
(list 2560.5625 539.5246) 
(list 2560.5625 539.5246) 
(list 2560.2625 549.5246) 
(list 2559.7375 549.5246) 
(list 2559.4375 539.5246) 
(list 2559.4375 539.5246) 
(list 2559.4375 538.5246) 
(list 2485.415 539.2746) 
(list 2485.415 534.3316) 
(list 2559.4375 535.0816) 
(list 2559.4375 534.0816) 
(list 2559.4375 534.0816) 
(list 2559.7375 524.0816)))
(apply 'command (append '("pline") coords '("c")))
(setq currobj (ssadd (entlast) currobj))
(command "_layer" "set" "prebias" "")
(setq coords (list 
(list 2559.4375 524.0816) 
(list 2559.4375 535.0816) 
(list 2485.415 534.3316) 
(list 2485.415 539.2746) 
(list 2559.4375 538.5246) 
(list 2559.4375 549.5246) 
(list 2560.5625 549.5246) 
(list 2560.5625 538.5246) 
(list 2634.585 539.2746) 
(list 2634.585 534.3316) 
(list 2560.5625 535.0816) 
(list 2560.5625 524.0816)))
(apply 'command (append '("pline") coords '("c")))
(setq currobj (ssadd (entlast) currobj))
(command "_layer" "set" "nitride" "")
(command "_layer" "set" "fda1" "")
(setq coords (list 
(list 2560.5625 535.2246) 
(list 2634.585 534.4746) 
(list 2634.585 534.6516) 
(list 2560.5625 535.3016)))
(apply 'command (append '("pline") coords '("c")))
(setq currobj (ssadd (entlast) currobj))
(setq coords (list 
(list 2560.5625 535.4446) 
(list 2634.585 534.7946) 
(list 2634.585 534.9716) 
(list 2560.5625 535.5216)))
(apply 'command (append '("pline") coords '("c")))
(setq currobj (ssadd (entlast) currobj))
(setq coords (list 
(list 2560.5625 535.6646) 
(list 2634.585 535.1146) 
(list 2634.585 535.2916) 
(list 2560.5625 535.7416)))
(apply 'command (append '("pline") coords '("c")))
(setq currobj (ssadd (entlast) currobj))
(setq coords (list 
(list 2560.5625 535.8846) 
(list 2634.585 535.4346) 
(list 2634.585 535.6116) 
(list 2560.5625 535.9616)))
(apply 'command (append '("pline") coords '("c")))
(setq currobj (ssadd (entlast) currobj))
(setq coords (list 
(list 2560.5625 536.1046) 
(list 2634.585 535.7546) 
(list 2634.585 535.9316) 
(list 2560.5625 536.1816)))
(apply 'command (append '("pline") coords '("c")))
(setq currobj (ssadd (entlast) currobj))
(setq coords (list 
(list 2560.5625 536.3246) 
(list 2634.585 536.0746) 
(list 2634.585 536.2516) 
(list 2560.5625 536.4016)))
(apply 'command (append '("pline") coords '("c")))
(setq currobj (ssadd (entlast) currobj))
(setq coords (list 
(list 2560.5625 536.5446) 
(list 2634.585 536.3946) 
(list 2634.585 536.5716) 
(list 2560.5625 536.6216)))
(apply 'command (append '("pline") coords '("c")))
(setq currobj (ssadd (entlast) currobj))
(setq coords (list 
(list 2560.5625 536.7646) 
(list 2634.585 536.7146) 
(list 2634.585 536.8916) 
(list 2560.5625 536.8416)))
(apply 'command (append '("pline") coords '("c")))
(setq currobj (ssadd (entlast) currobj))
(setq coords (list 
(list 2560.5625 536.9846) 
(list 2634.585 537.0346) 
(list 2634.585 537.2116) 
(list 2560.5625 537.0616)))
(apply 'command (append '("pline") coords '("c")))
(setq currobj (ssadd (entlast) currobj))
(setq coords (list 
(list 2560.5625 537.2046) 
(list 2634.585 537.3546) 
(list 2634.585 537.5316) 
(list 2560.5625 537.2816)))
(apply 'command (append '("pline") coords '("c")))
(setq currobj (ssadd (entlast) currobj))
(setq coords (list 
(list 2560.5625 537.4246) 
(list 2634.585 537.6746) 
(list 2634.585 537.8516) 
(list 2560.5625 537.5016)))
(apply 'command (append '("pline") coords '("c")))
(setq currobj (ssadd (entlast) currobj))
(setq coords (list 
(list 2560.5625 537.6446) 
(list 2634.585 537.9946) 
(list 2634.585 538.1716) 
(list 2560.5625 537.7216)))
(apply 'command (append '("pline") coords '("c")))
(setq currobj (ssadd (entlast) currobj))
(setq coords (list 
(list 2560.5625 537.8646) 
(list 2634.585 538.3146) 
(list 2634.585 538.4916) 
(list 2560.5625 537.9416)))
(apply 'command (append '("pline") coords '("c")))
(setq currobj (ssadd (entlast) currobj))
(setq coords (list 
(list 2560.5625 538.0846) 
(list 2634.585 538.6346) 
(list 2634.585 538.8116) 
(list 2560.5625 538.1616)))
(apply 'command (append '("pline") coords '("c")))
(setq currobj (ssadd (entlast) currobj))
(setq coords (list 
(list 2560.5625 538.3046) 
(list 2634.585 538.9546) 
(list 2634.585 539.1316) 
(list 2560.5625 538.3816)))
(apply 'command (append '("pline") coords '("c")))
(setq currobj (ssadd (entlast) currobj))
(setq coords (list 
(list 2559.4375 538.3816) 
(list 2485.415 539.1316) 
(list 2485.415 538.9546) 
(list 2559.4375 538.3046)))
(apply 'command (append '("pline") coords '("c")))
(setq currobj (ssadd (entlast) currobj))
(setq coords (list 
(list 2559.4375 538.1616) 
(list 2485.415 538.8116) 
(list 2485.415 538.6346) 
(list 2559.4375 538.0846)))
(apply 'command (append '("pline") coords '("c")))
(setq currobj (ssadd (entlast) currobj))
(setq coords (list 
(list 2559.4375 537.9416) 
(list 2485.415 538.4916) 
(list 2485.415 538.3146) 
(list 2559.4375 537.8646)))
(apply 'command (append '("pline") coords '("c")))
(setq currobj (ssadd (entlast) currobj))
(setq coords (list 
(list 2559.4375 537.7216) 
(list 2485.415 538.1716) 
(list 2485.415 537.9946) 
(list 2559.4375 537.6446)))
(apply 'command (append '("pline") coords '("c")))
(setq currobj (ssadd (entlast) currobj))
(setq coords (list 
(list 2559.4375 537.5016) 
(list 2485.415 537.8516) 
(list 2485.415 537.6746) 
(list 2559.4375 537.4246)))
(apply 'command (append '("pline") coords '("c")))
(setq currobj (ssadd (entlast) currobj))
(setq coords (list 
(list 2559.4375 537.2816) 
(list 2485.415 537.5316) 
(list 2485.415 537.3546) 
(list 2559.4375 537.2046)))
(apply 'command (append '("pline") coords '("c")))
(setq currobj (ssadd (entlast) currobj))
(setq coords (list 
(list 2559.4375 537.0616) 
(list 2485.415 537.2116) 
(list 2485.415 537.0346) 
(list 2559.4375 536.9846)))
(apply 'command (append '("pline") coords '("c")))
(setq currobj (ssadd (entlast) currobj))
(setq coords (list 
(list 2559.4375 536.8416) 
(list 2485.415 536.8916) 
(list 2485.415 536.7146) 
(list 2559.4375 536.7646)))
(apply 'command (append '("pline") coords '("c")))
(setq currobj (ssadd (entlast) currobj))
(setq coords (list 
(list 2559.4375 536.6216) 
(list 2485.415 536.5716) 
(list 2485.415 536.3946) 
(list 2559.4375 536.5446)))
(apply 'command (append '("pline") coords '("c")))
(setq currobj (ssadd (entlast) currobj))
(setq coords (list 
(list 2559.4375 536.4016) 
(list 2485.415 536.2516) 
(list 2485.415 536.0746) 
(list 2559.4375 536.3246)))
(apply 'command (append '("pline") coords '("c")))
(setq currobj (ssadd (entlast) currobj))
(setq coords (list 
(list 2559.4375 536.1816) 
(list 2485.415 535.9316) 
(list 2485.415 535.7546) 
(list 2559.4375 536.1046)))
(apply 'command (append '("pline") coords '("c")))
(setq currobj (ssadd (entlast) currobj))
(setq coords (list 
(list 2559.4375 535.9616) 
(list 2485.415 535.6116) 
(list 2485.415 535.4346) 
(list 2559.4375 535.8846)))
(apply 'command (append '("pline") coords '("c")))
(setq currobj (ssadd (entlast) currobj))
(setq coords (list 
(list 2559.4375 535.7416) 
(list 2485.415 535.2916) 
(list 2485.415 535.1146) 
(list 2559.4375 535.6646)))
(apply 'command (append '("pline") coords '("c")))
(setq currobj (ssadd (entlast) currobj))
(setq coords (list 
(list 2559.4375 535.5216) 
(list 2485.415 534.9716) 
(list 2485.415 534.7946) 
(list 2559.4375 535.4446)))
(apply 'command (append '("pline") coords '("c")))
(setq currobj (ssadd (entlast) currobj))
(setq coords (list 
(list 2559.4375 535.3016) 
(list 2485.415 534.6516) 
(list 2485.415 534.4746) 
(list 2559.4375 535.2246)))
(apply 'command (append '("pline") coords '("c")))
(setq currobj (ssadd (entlast) currobj))
(command "_layer" "set" "nitride" "")
(command "_layer" "set" "text" "")
(command "_circle" "2559.0625,524.0816" "0.075")
(command "_circle" "2559.0625,524.3816" "0.075")
(command "_circle" "2559.0625,524.6816" "0.075")
(command "_circle" "2559.0625,524.9816" "0.075")
(command "_circle" "2559.0625,525.2816" "0.075")
(command "_circle" "2558.7625,524.0816" "0.075")
(command "_circle" "2558.7625,524.3816" "0.075")
(command "_circle" "2558.7625,524.6816" "0.075")
(command "_circle" "2558.7625,524.9816" "0.075")
(command "_circle" "2558.7625,525.2816" "0.075")
(command "_circle" "2558.4625,524.0816" "0.075")
(command "_circle" "2558.4625,524.3816" "0.075")
(command "_circle" "2558.4625,524.6816" "0.075")
(command "_circle" "2558.4625,524.9816" "0.075")
(command "_circle" "2558.4625,525.2816" "0.075")
(command "_circle" "2558.1625,524.0816" "0.075")
(command "_circle" "2558.1625,524.3816" "0.075")
(command "_circle" "2558.1625,524.6816" "0.075")
(command "_circle" "2558.1625,524.9816" "0.075")
(command "_circle" "2558.1625,525.2816" "0.075")
(command "_circle" "2557.8625,524.0816" "0.075")
(command "_circle" "2557.8625,524.3816" "0.075")
(command "_circle" "2557.8625,524.6816" "0.075")
(command "_circle" "2557.8625,524.9816" "0.075")
(command "_circle" "2557.8625,525.2816" "0.075")
(command "_layer" "set" "nitride" "")
(setq coords (list 
(list 2560.2625 549.5246) 
(list 2560.2625 665.1693) 
(list 2559.7375 665.1693) 
(list 2559.7375 549.5246)))
(apply 'command (append '("pline") coords '("c")))
(setq currobj (ssadd (entlast) currobj))
(command "_layer" "set" "prebias" "")
(command "_rectangle" "2559.7375,549.5246" "2560.2625,665.1693")
(setq currobj (ssadd (entlast) currobj))
(command "_layer" "set" "nitride" "")
(setq coords (list 
(list 2560.2625 665.1693) 
(list 2560.5625 675.1693) 
(list 2560.5625 675.1693) 
(list 2560.5625 676.1693) 
(list 2634.585 675.4193) 
(list 2634.585 680.3623) 
(list 2560.5625 679.6123) 
(list 2560.5625 680.6123) 
(list 2560.5625 680.6123) 
(list 2560.2625 690.6123) 
(list 2559.7375 690.6123) 
(list 2559.4375 680.6123) 
(list 2559.4375 680.6123) 
(list 2559.4375 679.6123) 
(list 2485.415 680.3623) 
(list 2485.415 675.4193) 
(list 2559.4375 676.1693) 
(list 2559.4375 675.1693) 
(list 2559.4375 675.1693) 
(list 2559.7375 665.1693)))
(apply 'command (append '("pline") coords '("c")))
(setq currobj (ssadd (entlast) currobj))
(command "_layer" "set" "prebias" "")
(setq coords (list 
(list 2559.4375 665.1693) 
(list 2559.4375 676.1693) 
(list 2485.415 675.4193) 
(list 2485.415 680.3623) 
(list 2559.4375 679.6123) 
(list 2559.4375 690.6123) 
(list 2560.5625 690.6123) 
(list 2560.5625 679.6123) 
(list 2634.585 680.3623) 
(list 2634.585 675.4193) 
(list 2560.5625 676.1693) 
(list 2560.5625 665.1693)))
(apply 'command (append '("pline") coords '("c")))
(setq currobj (ssadd (entlast) currobj))
(command "_layer" "set" "nitride" "")
(command "_layer" "set" "fda1" "")
(setq coords (list 
(list 2560.5625 676.3123) 
(list 2634.585 675.5623) 
(list 2634.585 675.7393) 
(list 2560.5625 676.3893)))
(apply 'command (append '("pline") coords '("c")))
(setq currobj (ssadd (entlast) currobj))
(setq coords (list 
(list 2560.5625 676.5323) 
(list 2634.585 675.8823) 
(list 2634.585 676.0593) 
(list 2560.5625 676.6093)))
(apply 'command (append '("pline") coords '("c")))
(setq currobj (ssadd (entlast) currobj))
(setq coords (list 
(list 2560.5625 676.7523) 
(list 2634.585 676.2023) 
(list 2634.585 676.3793) 
(list 2560.5625 676.8293)))
(apply 'command (append '("pline") coords '("c")))
(setq currobj (ssadd (entlast) currobj))
(setq coords (list 
(list 2560.5625 676.9723) 
(list 2634.585 676.5223) 
(list 2634.585 676.6993) 
(list 2560.5625 677.0493)))
(apply 'command (append '("pline") coords '("c")))
(setq currobj (ssadd (entlast) currobj))
(setq coords (list 
(list 2560.5625 677.1923) 
(list 2634.585 676.8423) 
(list 2634.585 677.0193) 
(list 2560.5625 677.2693)))
(apply 'command (append '("pline") coords '("c")))
(setq currobj (ssadd (entlast) currobj))
(setq coords (list 
(list 2560.5625 677.4123) 
(list 2634.585 677.1623) 
(list 2634.585 677.3393) 
(list 2560.5625 677.4893)))
(apply 'command (append '("pline") coords '("c")))
(setq currobj (ssadd (entlast) currobj))
(setq coords (list 
(list 2560.5625 677.6323) 
(list 2634.585 677.4823) 
(list 2634.585 677.6593) 
(list 2560.5625 677.7093)))
(apply 'command (append '("pline") coords '("c")))
(setq currobj (ssadd (entlast) currobj))
(setq coords (list 
(list 2560.5625 677.8523) 
(list 2634.585 677.8023) 
(list 2634.585 677.9793) 
(list 2560.5625 677.9293)))
(apply 'command (append '("pline") coords '("c")))
(setq currobj (ssadd (entlast) currobj))
(setq coords (list 
(list 2560.5625 678.0723) 
(list 2634.585 678.1223) 
(list 2634.585 678.2993) 
(list 2560.5625 678.1493)))
(apply 'command (append '("pline") coords '("c")))
(setq currobj (ssadd (entlast) currobj))
(setq coords (list 
(list 2560.5625 678.2923) 
(list 2634.585 678.4423) 
(list 2634.585 678.6193) 
(list 2560.5625 678.3693)))
(apply 'command (append '("pline") coords '("c")))
(setq currobj (ssadd (entlast) currobj))
(setq coords (list 
(list 2560.5625 678.5123) 
(list 2634.585 678.7623) 
(list 2634.585 678.9393) 
(list 2560.5625 678.5893)))
(apply 'command (append '("pline") coords '("c")))
(setq currobj (ssadd (entlast) currobj))
(setq coords (list 
(list 2560.5625 678.7323) 
(list 2634.585 679.0823) 
(list 2634.585 679.2593) 
(list 2560.5625 678.8093)))
(apply 'command (append '("pline") coords '("c")))
(setq currobj (ssadd (entlast) currobj))
(setq coords (list 
(list 2560.5625 678.9523) 
(list 2634.585 679.4023) 
(list 2634.585 679.5793) 
(list 2560.5625 679.0293)))
(apply 'command (append '("pline") coords '("c")))
(setq currobj (ssadd (entlast) currobj))
(setq coords (list 
(list 2560.5625 679.1723) 
(list 2634.585 679.7223) 
(list 2634.585 679.8993) 
(list 2560.5625 679.2493)))
(apply 'command (append '("pline") coords '("c")))
(setq currobj (ssadd (entlast) currobj))
(setq coords (list 
(list 2560.5625 679.3923) 
(list 2634.585 680.0423) 
(list 2634.585 680.2193) 
(list 2560.5625 679.4693)))
(apply 'command (append '("pline") coords '("c")))
(setq currobj (ssadd (entlast) currobj))
(setq coords (list 
(list 2559.4375 679.4693) 
(list 2485.415 680.2193) 
(list 2485.415 680.0423) 
(list 2559.4375 679.3923)))
(apply 'command (append '("pline") coords '("c")))
(setq currobj (ssadd (entlast) currobj))
(setq coords (list 
(list 2559.4375 679.2493) 
(list 2485.415 679.8993) 
(list 2485.415 679.7223) 
(list 2559.4375 679.1723)))
(apply 'command (append '("pline") coords '("c")))
(setq currobj (ssadd (entlast) currobj))
(setq coords (list 
(list 2559.4375 679.0293) 
(list 2485.415 679.5793) 
(list 2485.415 679.4023) 
(list 2559.4375 678.9523)))
(apply 'command (append '("pline") coords '("c")))
(setq currobj (ssadd (entlast) currobj))
(setq coords (list 
(list 2559.4375 678.8093) 
(list 2485.415 679.2593) 
(list 2485.415 679.0823) 
(list 2559.4375 678.7323)))
(apply 'command (append '("pline") coords '("c")))
(setq currobj (ssadd (entlast) currobj))
(setq coords (list 
(list 2559.4375 678.5893) 
(list 2485.415 678.9393) 
(list 2485.415 678.7623) 
(list 2559.4375 678.5123)))
(apply 'command (append '("pline") coords '("c")))
(setq currobj (ssadd (entlast) currobj))
(setq coords (list 
(list 2559.4375 678.3693) 
(list 2485.415 678.6193) 
(list 2485.415 678.4423) 
(list 2559.4375 678.2923)))
(apply 'command (append '("pline") coords '("c")))
(setq currobj (ssadd (entlast) currobj))
(setq coords (list 
(list 2559.4375 678.1493) 
(list 2485.415 678.2993) 
(list 2485.415 678.1223) 
(list 2559.4375 678.0723)))
(apply 'command (append '("pline") coords '("c")))
(setq currobj (ssadd (entlast) currobj))
(setq coords (list 
(list 2559.4375 677.9293) 
(list 2485.415 677.9793) 
(list 2485.415 677.8023) 
(list 2559.4375 677.8523)))
(apply 'command (append '("pline") coords '("c")))
(setq currobj (ssadd (entlast) currobj))
(setq coords (list 
(list 2559.4375 677.7093) 
(list 2485.415 677.6593) 
(list 2485.415 677.4823) 
(list 2559.4375 677.6323)))
(apply 'command (append '("pline") coords '("c")))
(setq currobj (ssadd (entlast) currobj))
(setq coords (list 
(list 2559.4375 677.4893) 
(list 2485.415 677.3393) 
(list 2485.415 677.1623) 
(list 2559.4375 677.4123)))
(apply 'command (append '("pline") coords '("c")))
(setq currobj (ssadd (entlast) currobj))
(setq coords (list 
(list 2559.4375 677.2693) 
(list 2485.415 677.0193) 
(list 2485.415 676.8423) 
(list 2559.4375 677.1923)))
(apply 'command (append '("pline") coords '("c")))
(setq currobj (ssadd (entlast) currobj))
(setq coords (list 
(list 2559.4375 677.0493) 
(list 2485.415 676.6993) 
(list 2485.415 676.5223) 
(list 2559.4375 676.9723)))
(apply 'command (append '("pline") coords '("c")))
(setq currobj (ssadd (entlast) currobj))
(setq coords (list 
(list 2559.4375 676.8293) 
(list 2485.415 676.3793) 
(list 2485.415 676.2023) 
(list 2559.4375 676.7523)))
(apply 'command (append '("pline") coords '("c")))
(setq currobj (ssadd (entlast) currobj))
(setq coords (list 
(list 2559.4375 676.6093) 
(list 2485.415 676.0593) 
(list 2485.415 675.8823) 
(list 2559.4375 676.5323)))
(apply 'command (append '("pline") coords '("c")))
(setq currobj (ssadd (entlast) currobj))
(setq coords (list 
(list 2559.4375 676.3893) 
(list 2485.415 675.7393) 
(list 2485.415 675.5623) 
(list 2559.4375 676.3123)))
(apply 'command (append '("pline") coords '("c")))
(setq currobj (ssadd (entlast) currobj))
(command "_layer" "set" "nitride" "")
(command "_layer" "set" "text" "")
(command "_circle" "2559.0625,665.1693" "0.075")
(command "_circle" "2559.0625,665.4693" "0.075")
(command "_circle" "2559.0625,665.7693" "0.075")
(command "_circle" "2559.0625,666.0693" "0.075")
(command "_circle" "2559.0625,666.3693" "0.075")
(command "_circle" "2558.7625,665.1693" "0.075")
(command "_circle" "2558.7625,665.4693" "0.075")
(command "_circle" "2558.7625,665.7693" "0.075")
(command "_circle" "2558.7625,666.0693" "0.075")
(command "_circle" "2558.7625,666.3693" "0.075")
(command "_circle" "2558.4625,665.1693" "0.075")
(command "_circle" "2558.4625,665.4693" "0.075")
(command "_circle" "2558.4625,665.7693" "0.075")
(command "_circle" "2558.4625,666.0693" "0.075")
(command "_circle" "2558.4625,666.3693" "0.075")
(command "_circle" "2558.1625,665.1693" "0.075")
(command "_circle" "2558.1625,665.4693" "0.075")
(command "_circle" "2558.1625,665.7693" "0.075")
(command "_circle" "2558.1625,666.0693" "0.075")
(command "_circle" "2558.1625,666.3693" "0.075")
(command "_circle" "2557.8625,665.1693" "0.075")
(command "_circle" "2557.8625,665.4693" "0.075")
(command "_circle" "2557.8625,665.7693" "0.075")
(command "_circle" "2557.8625,666.0693" "0.075")
(command "_circle" "2557.8625,666.3693" "0.075")
(command "_layer" "set" "nitride" "")
(setq coords (list 
(list 2560.2625 690.6123) 
(list 2560.2625 806.257) 
(list 2559.7375 806.257) 
(list 2559.7375 690.6123)))
(apply 'command (append '("pline") coords '("c")))
(setq currobj (ssadd (entlast) currobj))
(command "_layer" "set" "prebias" "")
(command "_rectangle" "2559.7375,690.6123" "2560.2625,806.257")
(setq currobj (ssadd (entlast) currobj))
(command "_layer" "set" "nitride" "")
(setq coords (list 
(list 2560.2625 806.257) 
(list 2560.5625 816.257) 
(list 2560.5625 816.257) 
(list 2560.5625 817.257) 
(list 2634.585 816.507) 
(list 2634.585 821.45) 
(list 2560.5625 820.7) 
(list 2560.5625 821.7) 
(list 2560.5625 821.7) 
(list 2560.2625 831.7) 
(list 2559.7375 831.7) 
(list 2559.4375 821.7) 
(list 2559.4375 821.7) 
(list 2559.4375 820.7) 
(list 2485.415 821.45) 
(list 2485.415 816.507) 
(list 2559.4375 817.257) 
(list 2559.4375 816.257) 
(list 2559.4375 816.257) 
(list 2559.7375 806.257)))
(apply 'command (append '("pline") coords '("c")))
(setq currobj (ssadd (entlast) currobj))
(command "_layer" "set" "prebias" "")
(setq coords (list 
(list 2559.4375 806.257) 
(list 2559.4375 817.257) 
(list 2485.415 816.507) 
(list 2485.415 821.45) 
(list 2559.4375 820.7) 
(list 2559.4375 831.7) 
(list 2560.5625 831.7) 
(list 2560.5625 820.7) 
(list 2634.585 821.45) 
(list 2634.585 816.507) 
(list 2560.5625 817.257) 
(list 2560.5625 806.257)))
(apply 'command (append '("pline") coords '("c")))
(setq currobj (ssadd (entlast) currobj))
(command "_layer" "set" "nitride" "")
(command "_layer" "set" "fda1" "")
(setq coords (list 
(list 2560.5625 817.4) 
(list 2634.585 816.65) 
(list 2634.585 816.827) 
(list 2560.5625 817.477)))
(apply 'command (append '("pline") coords '("c")))
(setq currobj (ssadd (entlast) currobj))
(setq coords (list 
(list 2560.5625 817.62) 
(list 2634.585 816.97) 
(list 2634.585 817.147) 
(list 2560.5625 817.697)))
(apply 'command (append '("pline") coords '("c")))
(setq currobj (ssadd (entlast) currobj))
(setq coords (list 
(list 2560.5625 817.84) 
(list 2634.585 817.29) 
(list 2634.585 817.467) 
(list 2560.5625 817.917)))
(apply 'command (append '("pline") coords '("c")))
(setq currobj (ssadd (entlast) currobj))
(setq coords (list 
(list 2560.5625 818.06) 
(list 2634.585 817.61) 
(list 2634.585 817.787) 
(list 2560.5625 818.137)))
(apply 'command (append '("pline") coords '("c")))
(setq currobj (ssadd (entlast) currobj))
(setq coords (list 
(list 2560.5625 818.28) 
(list 2634.585 817.93) 
(list 2634.585 818.107) 
(list 2560.5625 818.357)))
(apply 'command (append '("pline") coords '("c")))
(setq currobj (ssadd (entlast) currobj))
(setq coords (list 
(list 2560.5625 818.5) 
(list 2634.585 818.25) 
(list 2634.585 818.427) 
(list 2560.5625 818.577)))
(apply 'command (append '("pline") coords '("c")))
(setq currobj (ssadd (entlast) currobj))
(setq coords (list 
(list 2560.5625 818.72) 
(list 2634.585 818.57) 
(list 2634.585 818.747) 
(list 2560.5625 818.797)))
(apply 'command (append '("pline") coords '("c")))
(setq currobj (ssadd (entlast) currobj))
(setq coords (list 
(list 2560.5625 818.94) 
(list 2634.585 818.89) 
(list 2634.585 819.067) 
(list 2560.5625 819.017)))
(apply 'command (append '("pline") coords '("c")))
(setq currobj (ssadd (entlast) currobj))
(setq coords (list 
(list 2560.5625 819.16) 
(list 2634.585 819.21) 
(list 2634.585 819.387) 
(list 2560.5625 819.237)))
(apply 'command (append '("pline") coords '("c")))
(setq currobj (ssadd (entlast) currobj))
(setq coords (list 
(list 2560.5625 819.38) 
(list 2634.585 819.53) 
(list 2634.585 819.707) 
(list 2560.5625 819.457)))
(apply 'command (append '("pline") coords '("c")))
(setq currobj (ssadd (entlast) currobj))
(setq coords (list 
(list 2560.5625 819.6) 
(list 2634.585 819.85) 
(list 2634.585 820.027) 
(list 2560.5625 819.677)))
(apply 'command (append '("pline") coords '("c")))
(setq currobj (ssadd (entlast) currobj))
(setq coords (list 
(list 2560.5625 819.82) 
(list 2634.585 820.17) 
(list 2634.585 820.347) 
(list 2560.5625 819.897)))
(apply 'command (append '("pline") coords '("c")))
(setq currobj (ssadd (entlast) currobj))
(setq coords (list 
(list 2560.5625 820.04) 
(list 2634.585 820.49) 
(list 2634.585 820.667) 
(list 2560.5625 820.117)))
(apply 'command (append '("pline") coords '("c")))
(setq currobj (ssadd (entlast) currobj))
(setq coords (list 
(list 2560.5625 820.26) 
(list 2634.585 820.81) 
(list 2634.585 820.987) 
(list 2560.5625 820.337)))
(apply 'command (append '("pline") coords '("c")))
(setq currobj (ssadd (entlast) currobj))
(setq coords (list 
(list 2560.5625 820.48) 
(list 2634.585 821.13) 
(list 2634.585 821.307) 
(list 2560.5625 820.557)))
(apply 'command (append '("pline") coords '("c")))
(setq currobj (ssadd (entlast) currobj))
(setq coords (list 
(list 2559.4375 820.557) 
(list 2485.415 821.307) 
(list 2485.415 821.13) 
(list 2559.4375 820.48)))
(apply 'command (append '("pline") coords '("c")))
(setq currobj (ssadd (entlast) currobj))
(setq coords (list 
(list 2559.4375 820.337) 
(list 2485.415 820.987) 
(list 2485.415 820.81) 
(list 2559.4375 820.26)))
(apply 'command (append '("pline") coords '("c")))
(setq currobj (ssadd (entlast) currobj))
(setq coords (list 
(list 2559.4375 820.117) 
(list 2485.415 820.667) 
(list 2485.415 820.49) 
(list 2559.4375 820.04)))
(apply 'command (append '("pline") coords '("c")))
(setq currobj (ssadd (entlast) currobj))
(setq coords (list 
(list 2559.4375 819.897) 
(list 2485.415 820.347) 
(list 2485.415 820.17) 
(list 2559.4375 819.82)))
(apply 'command (append '("pline") coords '("c")))
(setq currobj (ssadd (entlast) currobj))
(setq coords (list 
(list 2559.4375 819.677) 
(list 2485.415 820.027) 
(list 2485.415 819.85) 
(list 2559.4375 819.6)))
(apply 'command (append '("pline") coords '("c")))
(setq currobj (ssadd (entlast) currobj))
(setq coords (list 
(list 2559.4375 819.457) 
(list 2485.415 819.707) 
(list 2485.415 819.53) 
(list 2559.4375 819.38)))
(apply 'command (append '("pline") coords '("c")))
(setq currobj (ssadd (entlast) currobj))
(setq coords (list 
(list 2559.4375 819.237) 
(list 2485.415 819.387) 
(list 2485.415 819.21) 
(list 2559.4375 819.16)))
(apply 'command (append '("pline") coords '("c")))
(setq currobj (ssadd (entlast) currobj))
(setq coords (list 
(list 2559.4375 819.017) 
(list 2485.415 819.067) 
(list 2485.415 818.89) 
(list 2559.4375 818.94)))
(apply 'command (append '("pline") coords '("c")))
(setq currobj (ssadd (entlast) currobj))
(setq coords (list 
(list 2559.4375 818.797) 
(list 2485.415 818.747) 
(list 2485.415 818.57) 
(list 2559.4375 818.72)))
(apply 'command (append '("pline") coords '("c")))
(setq currobj (ssadd (entlast) currobj))
(setq coords (list 
(list 2559.4375 818.577) 
(list 2485.415 818.427) 
(list 2485.415 818.25) 
(list 2559.4375 818.5)))
(apply 'command (append '("pline") coords '("c")))
(setq currobj (ssadd (entlast) currobj))
(setq coords (list 
(list 2559.4375 818.357) 
(list 2485.415 818.107) 
(list 2485.415 817.93) 
(list 2559.4375 818.28)))
(apply 'command (append '("pline") coords '("c")))
(setq currobj (ssadd (entlast) currobj))
(setq coords (list 
(list 2559.4375 818.137) 
(list 2485.415 817.787) 
(list 2485.415 817.61) 
(list 2559.4375 818.06)))
(apply 'command (append '("pline") coords '("c")))
(setq currobj (ssadd (entlast) currobj))
(setq coords (list 
(list 2559.4375 817.917) 
(list 2485.415 817.467) 
(list 2485.415 817.29) 
(list 2559.4375 817.84)))
(apply 'command (append '("pline") coords '("c")))
(setq currobj (ssadd (entlast) currobj))
(setq coords (list 
(list 2559.4375 817.697) 
(list 2485.415 817.147) 
(list 2485.415 816.97) 
(list 2559.4375 817.62)))
(apply 'command (append '("pline") coords '("c")))
(setq currobj (ssadd (entlast) currobj))
(setq coords (list 
(list 2559.4375 817.477) 
(list 2485.415 816.827) 
(list 2485.415 816.65) 
(list 2559.4375 817.4)))
(apply 'command (append '("pline") coords '("c")))
(setq currobj (ssadd (entlast) currobj))
(command "_layer" "set" "nitride" "")
(command "_layer" "set" "text" "")
(command "_circle" "2559.0625,806.257" "0.075")
(command "_circle" "2559.0625,806.557" "0.075")
(command "_circle" "2559.0625,806.857" "0.075")
(command "_circle" "2559.0625,807.157" "0.075")
(command "_circle" "2559.0625,807.457" "0.075")
(command "_circle" "2558.7625,806.257" "0.075")
(command "_circle" "2558.7625,806.557" "0.075")
(command "_circle" "2558.7625,806.857" "0.075")
(command "_circle" "2558.7625,807.157" "0.075")
(command "_circle" "2558.7625,807.457" "0.075")
(command "_circle" "2558.4625,806.257" "0.075")
(command "_circle" "2558.4625,806.557" "0.075")
(command "_circle" "2558.4625,806.857" "0.075")
(command "_circle" "2558.4625,807.157" "0.075")
(command "_circle" "2558.4625,807.457" "0.075")
(command "_circle" "2558.1625,806.257" "0.075")
(command "_circle" "2558.1625,806.557" "0.075")
(command "_circle" "2558.1625,806.857" "0.075")
(command "_circle" "2558.1625,807.157" "0.075")
(command "_circle" "2558.1625,807.457" "0.075")
(command "_circle" "2557.8625,806.257" "0.075")
(command "_circle" "2557.8625,806.557" "0.075")
(command "_circle" "2557.8625,806.857" "0.075")
(command "_circle" "2557.8625,807.157" "0.075")
(command "_circle" "2557.8625,807.457" "0.075")
(command "_layer" "set" "nitride" "")
(setq coords (list 
(list 2560.2625 831.7) 
(list 2560.2625 836.7) 
(list 2559.7375 836.7) 
(list 2559.7375 831.7)))
(apply 'command (append '("pline") coords '("c")))
(setq currobj (ssadd (entlast) currobj))
(command "_layer" "set" "prebias" "")
(command "_rectangle" "2559.7375,831.7" "2560.2625,836.7")
(setq currobj (ssadd (entlast) currobj))
(command "_layer" "set" "nitride" "")
(setq cooledsinglenanobeam8 currobj)
(setq currobj nil)
(setq currobj (ssadd))
; DRAWING PHOTONIC CRYSTAL
(command "_layer" "set" "negYjunc" "")
(setq coords (list 
(list 2560.135 866.7) 
(list 2560 851.7) 
(list 2560 866.7)))
(apply 'command (append '("pline") coords '("c")))
(setq currobj (ssadd (entlast) currobj))
(setq coords (list 
(list 2560.2625 836.7) 
(list 2560.415 866.7) 
(list 2561.129 866.7) 
(list 2561.129 836.7)))
(apply 'command (append '("pline") coords '("c")))
(setq currobj (ssadd (entlast) currobj))
(setq coords (list 
(list 2559.865 866.7) 
(list 2560 851.7) 
(list 2560 866.7)))
(apply 'command (append '("pline") coords '("c")))
(setq currobj (ssadd (entlast) currobj))
(setq coords (list 
(list 2559.7375 836.7) 
(list 2559.585 866.7) 
(list 2558.871 866.7) 
(list 2558.871 836.7)))
(apply 'command (append '("pline") coords '("c")))
(setq currobj (ssadd (entlast) currobj))
(command "_layer" "set" "nitride" "")
(setq yjunction8 currobj)
(setq currobj nil)
(setq currobj (ssadd))
(setq tap8 nil)
(setq tap8 (ssadd))
(command "_layer" "set" "phc" "")
(setq coords (list 
(list 2560 866.7) 
(list 2560.135 866.7) 
(list 2560.135 866.7103) 
(list 2560.135 866.7206) 
(list 2560.135 866.7308) 
(list 2560.135 866.7411) 
(list 2560.135 866.7514) 
(list 2560.135 866.7617) 
(list 2560.135 866.7719) 
(list 2560.135 866.7822) 
(list 2560.135 866.7925) 
(list 2560.135 866.8028) 
(list 2560.135 866.8131) 
(list 2560.135 866.8233) 
(list 2560.135 866.8336) 
(list 2560.135 866.8439) 
(list 2560.135 866.8542) 
(list 2560.135 866.8644) 
(list 2560.135 866.8747) 
(list 2560.135 866.885) 
(list 2560.135 866.8953) 
(list 2560.135 866.9056) 
(list 2560.135 866.9158) 
(list 2560.135 866.9261) 
(list 2560.135 866.9364) 
(list 2560.135 866.9467) 
(list 2560.135 866.9569) 
(list 2560.135 866.9672) 
(list 2560.135 866.9775) 
(list 2560.135 866.9878) 
(list 2560.135 866.9981) 
(list 2560.135 867.0083) 
(list 2560.135 867.0186) 
(list 2560.135 867.0289) 
(list 2560.135 867.0392) 
(list 2560.135 867.0494) 
(list 2560.135 867.0597) 
(list 2560.135 867.07) 
(list 2560 867.07)))
(apply 'command (append '("pline") coords '("c")))
(setq tap8 (ssadd (entlast) tap8))
(command "_mirror" (entlast) "" "2560,900" "2560,901" "No")
(setq tap8 (ssadd (entlast) tap8))
(setq coords (list 
(list 2560.425 866.7) 
(list 2560.415 866.7) 
(list 2560.4153 866.7103) 
(list 2560.4155 866.7206) 
(list 2560.4157 866.7308) 
(list 2560.4159 866.7411) 
(list 2560.4159 866.7514) 
(list 2560.4159 866.7617) 
(list 2560.4158 866.7719) 
(list 2560.4156 866.7822) 
(list 2560.4152 866.7925) 
(list 2560.4148 866.8028) 
(list 2560.4143 866.8131) 
(list 2560.4138 866.8233) 
(list 2560.4132 866.8336) 
(list 2560.4127 866.8439) 
(list 2560.4121 866.8542) 
(list 2560.4116 866.8644) 
(list 2560.4112 866.8747) 
(list 2560.4109 866.885) 
(list 2560.4108 866.8953) 
(list 2560.4108 866.9056) 
(list 2560.411 866.9158) 
(list 2560.4113 866.9261) 
(list 2560.4119 866.9364) 
(list 2560.4126 866.9467) 
(list 2560.4135 866.9569) 
(list 2560.4145 866.9672) 
(list 2560.4157 866.9775) 
(list 2560.4169 866.9878) 
(list 2560.4182 866.9981) 
(list 2560.4195 867.0083) 
(list 2560.4208 867.0186) 
(list 2560.422 867.0289) 
(list 2560.423 867.0392) 
(list 2560.4239 867.0494) 
(list 2560.4246 867.0597) 
(list 2560.425 867.07) 
(list 2560.425 867.07)))
(apply 'command (append '("pline") coords '("c")))
(setq tap8 (ssadd (entlast) tap8))
(command "_mirror" (entlast) "" "2560,900" "2560,901" "No")
(setq tap8 (ssadd (entlast) tap8))
(setq coords (list 
(list 2561.129 866.7) 
(list 2560.425 866.7) 
(list 2560.425 866.7103) 
(list 2560.425 866.7206) 
(list 2560.425 866.7308) 
(list 2560.425 866.7411) 
(list 2560.425 866.7514) 
(list 2560.425 866.7617) 
(list 2560.425 866.7719) 
(list 2560.425 866.7822) 
(list 2560.425 866.7925) 
(list 2560.425 866.8028) 
(list 2560.425 866.8131) 
(list 2560.425 866.8233) 
(list 2560.425 866.8336) 
(list 2560.425 866.8439) 
(list 2560.425 866.8542) 
(list 2560.425 866.8644) 
(list 2560.425 866.8747) 
(list 2560.425 866.885) 
(list 2560.425 866.8953) 
(list 2560.425 866.9056) 
(list 2560.425 866.9158) 
(list 2560.425 866.9261) 
(list 2560.425 866.9364) 
(list 2560.425 866.9467) 
(list 2560.425 866.9569) 
(list 2560.425 866.9672) 
(list 2560.425 866.9775) 
(list 2560.425 866.9878) 
(list 2560.425 866.9981) 
(list 2560.425 867.0083) 
(list 2560.425 867.0186) 
(list 2560.425 867.0289) 
(list 2560.425 867.0392) 
(list 2560.425 867.0494) 
(list 2560.425 867.0597) 
(list 2560.425 867.07) 
(list 2561.129 867.07)))
(apply 'command (append '("pline") coords '("c")))
(setq tap8 (ssadd (entlast) tap8))
(command "_mirror" (entlast) "" "2560,900" "2560,901" "No")
(setq tap8 (ssadd (entlast) tap8))
(setq coords (list 
(list 2560 867.07) 
(list 2560.135 867.07) 
(list 2560.135 867.0803) 
(list 2560.135 867.0906) 
(list 2560.135 867.1008) 
(list 2560.135 867.1111) 
(list 2560.135 867.1214) 
(list 2560.135 867.1317) 
(list 2560.135 867.1419) 
(list 2560.135 867.1522) 
(list 2560.135 867.1625) 
(list 2560.135 867.1728) 
(list 2560.135 867.1831) 
(list 2560.135 867.1933) 
(list 2560.135 867.2036) 
(list 2560.135 867.2139) 
(list 2560.135 867.2242) 
(list 2560.135 867.2344) 
(list 2560.135 867.2447) 
(list 2560.135 867.255) 
(list 2560.135 867.2653) 
(list 2560.135 867.2756) 
(list 2560.135 867.2858) 
(list 2560.135 867.2961) 
(list 2560.135 867.3064) 
(list 2560.135 867.3167) 
(list 2560.135 867.3269) 
(list 2560.135 867.3372) 
(list 2560.135 867.3475) 
(list 2560.135 867.3578) 
(list 2560.135 867.3681) 
(list 2560.135 867.3783) 
(list 2560.135 867.3886) 
(list 2560.135 867.3989) 
(list 2560.135 867.4092) 
(list 2560.135 867.4194) 
(list 2560.135 867.4297) 
(list 2560.135 867.44) 
(list 2560 867.44)))
(apply 'command (append '("pline") coords '("c")))
(setq tap8 (ssadd (entlast) tap8))
(command "_mirror" (entlast) "" "2560,900" "2560,901" "No")
(setq tap8 (ssadd (entlast) tap8))
(setq coords (list 
(list 2560.4349 867.07) 
(list 2560.425 867.07) 
(list 2560.4251 867.0803) 
(list 2560.4249 867.0906) 
(list 2560.4245 867.1008) 
(list 2560.4237 867.1111) 
(list 2560.4227 867.1214) 
(list 2560.4214 867.1317) 
(list 2560.4198 867.1419) 
(list 2560.4181 867.1522) 
(list 2560.4162 867.1625) 
(list 2560.4142 867.1728) 
(list 2560.4122 867.1831) 
(list 2560.4102 867.1933) 
(list 2560.4084 867.2036) 
(list 2560.4067 867.2139) 
(list 2560.4052 867.2242) 
(list 2560.4041 867.2344) 
(list 2560.4033 867.2447) 
(list 2560.4028 867.255) 
(list 2560.4028 867.2653) 
(list 2560.4032 867.2756) 
(list 2560.4041 867.2858) 
(list 2560.4054 867.2961) 
(list 2560.407 867.3064) 
(list 2560.409 867.3167) 
(list 2560.4113 867.3269) 
(list 2560.4139 867.3372) 
(list 2560.4166 867.3475) 
(list 2560.4194 867.3578) 
(list 2560.4223 867.3681) 
(list 2560.425 867.3783) 
(list 2560.4275 867.3886) 
(list 2560.4298 867.3989) 
(list 2560.4318 867.4092) 
(list 2560.4333 867.4194) 
(list 2560.4344 867.4297) 
(list 2560.4349 867.44) 
(list 2560.4349 867.44)))
(apply 'command (append '("pline") coords '("c")))
(setq tap8 (ssadd (entlast) tap8))
(command "_mirror" (entlast) "" "2560,900" "2560,901" "No")
(setq tap8 (ssadd (entlast) tap8))
(setq coords (list 
(list 2561.129 867.07) 
(list 2560.4349 867.07) 
(list 2560.4349 867.0803) 
(list 2560.4349 867.0906) 
(list 2560.4349 867.1008) 
(list 2560.4349 867.1111) 
(list 2560.4349 867.1214) 
(list 2560.4349 867.1317) 
(list 2560.4349 867.1419) 
(list 2560.4349 867.1522) 
(list 2560.4349 867.1625) 
(list 2560.4349 867.1728) 
(list 2560.4349 867.1831) 
(list 2560.4349 867.1933) 
(list 2560.4349 867.2036) 
(list 2560.4349 867.2139) 
(list 2560.4349 867.2242) 
(list 2560.4349 867.2344) 
(list 2560.4349 867.2447) 
(list 2560.4349 867.255) 
(list 2560.4349 867.2653) 
(list 2560.4349 867.2756) 
(list 2560.4349 867.2858) 
(list 2560.4349 867.2961) 
(list 2560.4349 867.3064) 
(list 2560.4349 867.3167) 
(list 2560.4349 867.3269) 
(list 2560.4349 867.3372) 
(list 2560.4349 867.3475) 
(list 2560.4349 867.3578) 
(list 2560.4349 867.3681) 
(list 2560.4349 867.3783) 
(list 2560.4349 867.3886) 
(list 2560.4349 867.3989) 
(list 2560.4349 867.4092) 
(list 2560.4349 867.4194) 
(list 2560.4349 867.4297) 
(list 2560.4349 867.44) 
(list 2561.129 867.44)))
(apply 'command (append '("pline") coords '("c")))
(setq tap8 (ssadd (entlast) tap8))
(command "_mirror" (entlast) "" "2560,900" "2560,901" "No")
(setq tap8 (ssadd (entlast) tap8))
(setq coords (list 
(list 2560 867.44) 
(list 2560.135 867.44) 
(list 2560.135 867.4503) 
(list 2560.135 867.4606) 
(list 2560.135 867.4708) 
(list 2560.135 867.4811) 
(list 2560.135 867.4914) 
(list 2560.135 867.5017) 
(list 2560.135 867.5119) 
(list 2560.135 867.5222) 
(list 2560.135 867.5325) 
(list 2560.135 867.5428) 
(list 2560.135 867.5531) 
(list 2560.135 867.5633) 
(list 2560.135 867.5736) 
(list 2560.135 867.5839) 
(list 2560.135 867.5942) 
(list 2560.135 867.6044) 
(list 2560.135 867.6147) 
(list 2560.135 867.625) 
(list 2560.135 867.6353) 
(list 2560.135 867.6456) 
(list 2560.135 867.6558) 
(list 2560.135 867.6661) 
(list 2560.135 867.6764) 
(list 2560.135 867.6867) 
(list 2560.135 867.6969) 
(list 2560.135 867.7072) 
(list 2560.135 867.7175) 
(list 2560.135 867.7278) 
(list 2560.135 867.7381) 
(list 2560.135 867.7483) 
(list 2560.135 867.7586) 
(list 2560.135 867.7689) 
(list 2560.135 867.7792) 
(list 2560.135 867.7894) 
(list 2560.135 867.7997) 
(list 2560.135 867.81) 
(list 2560 867.81)))
(apply 'command (append '("pline") coords '("c")))
(setq tap8 (ssadd (entlast) tap8))
(command "_mirror" (entlast) "" "2560,900" "2560,901" "No")
(setq tap8 (ssadd (entlast) tap8))
(setq coords (list 
(list 2560.4449 867.44) 
(list 2560.4349 867.44) 
(list 2560.4349 867.4503) 
(list 2560.4344 867.4606) 
(list 2560.4332 867.4708) 
(list 2560.4316 867.4811) 
(list 2560.4294 867.4914) 
(list 2560.4268 867.5017) 
(list 2560.4238 867.5119) 
(list 2560.4206 867.5222) 
(list 2560.4171 867.5325) 
(list 2560.4136 867.5428) 
(list 2560.41 867.5531) 
(list 2560.4066 867.5633) 
(list 2560.4035 867.5736) 
(list 2560.4007 867.5839) 
(list 2560.3983 867.5942) 
(list 2560.3965 867.6044) 
(list 2560.3953 867.6147) 
(list 2560.3947 867.625) 
(list 2560.3949 867.6353) 
(list 2560.3957 867.6456) 
(list 2560.3972 867.6558) 
(list 2560.3994 867.6661) 
(list 2560.4021 867.6764) 
(list 2560.4054 867.6867) 
(list 2560.4092 867.6969) 
(list 2560.4133 867.7072) 
(list 2560.4176 867.7175) 
(list 2560.4219 867.7278) 
(list 2560.4263 867.7381) 
(list 2560.4304 867.7483) 
(list 2560.4343 867.7586) 
(list 2560.4377 867.7689) 
(list 2560.4405 867.7792) 
(list 2560.4427 867.7894) 
(list 2560.4442 867.7997) 
(list 2560.4449 867.81) 
(list 2560.4449 867.81)))
(apply 'command (append '("pline") coords '("c")))
(setq tap8 (ssadd (entlast) tap8))
(command "_mirror" (entlast) "" "2560,900" "2560,901" "No")
(setq tap8 (ssadd (entlast) tap8))
(setq coords (list 
(list 2561.129 867.44) 
(list 2560.4449 867.44) 
(list 2560.4449 867.4503) 
(list 2560.4449 867.4606) 
(list 2560.4449 867.4708) 
(list 2560.4449 867.4811) 
(list 2560.4449 867.4914) 
(list 2560.4449 867.5017) 
(list 2560.4449 867.5119) 
(list 2560.4449 867.5222) 
(list 2560.4449 867.5325) 
(list 2560.4449 867.5428) 
(list 2560.4449 867.5531) 
(list 2560.4449 867.5633) 
(list 2560.4449 867.5736) 
(list 2560.4449 867.5839) 
(list 2560.4449 867.5942) 
(list 2560.4449 867.6044) 
(list 2560.4449 867.6147) 
(list 2560.4449 867.625) 
(list 2560.4449 867.6353) 
(list 2560.4449 867.6456) 
(list 2560.4449 867.6558) 
(list 2560.4449 867.6661) 
(list 2560.4449 867.6764) 
(list 2560.4449 867.6867) 
(list 2560.4449 867.6969) 
(list 2560.4449 867.7072) 
(list 2560.4449 867.7175) 
(list 2560.4449 867.7278) 
(list 2560.4449 867.7381) 
(list 2560.4449 867.7483) 
(list 2560.4449 867.7586) 
(list 2560.4449 867.7689) 
(list 2560.4449 867.7792) 
(list 2560.4449 867.7894) 
(list 2560.4449 867.7997) 
(list 2560.4449 867.81) 
(list 2561.129 867.81)))
(apply 'command (append '("pline") coords '("c")))
(setq tap8 (ssadd (entlast) tap8))
(command "_mirror" (entlast) "" "2560,900" "2560,901" "No")
(setq tap8 (ssadd (entlast) tap8))
(setq coords (list 
(list 2560 867.81) 
(list 2560.135 867.81) 
(list 2560.135 867.8203) 
(list 2560.135 867.8306) 
(list 2560.135 867.8408) 
(list 2560.135 867.8511) 
(list 2560.135 867.8614) 
(list 2560.135 867.8717) 
(list 2560.135 867.8819) 
(list 2560.135 867.8922) 
(list 2560.135 867.9025) 
(list 2560.135 867.9128) 
(list 2560.135 867.9231) 
(list 2560.135 867.9333) 
(list 2560.135 867.9436) 
(list 2560.135 867.9539) 
(list 2560.135 867.9642) 
(list 2560.135 867.9744) 
(list 2560.135 867.9847) 
(list 2560.135 867.995) 
(list 2560.135 868.0053) 
(list 2560.135 868.0156) 
(list 2560.135 868.0258) 
(list 2560.135 868.0361) 
(list 2560.135 868.0464) 
(list 2560.135 868.0567) 
(list 2560.135 868.0669) 
(list 2560.135 868.0772) 
(list 2560.135 868.0875) 
(list 2560.135 868.0978) 
(list 2560.135 868.1081) 
(list 2560.135 868.1183) 
(list 2560.135 868.1286) 
(list 2560.135 868.1389) 
(list 2560.135 868.1492) 
(list 2560.135 868.1594) 
(list 2560.135 868.1697) 
(list 2560.135 868.18) 
(list 2560 868.18)))
(apply 'command (append '("pline") coords '("c")))
(setq tap8 (ssadd (entlast) tap8))
(command "_mirror" (entlast) "" "2560,900" "2560,901" "No")
(setq tap8 (ssadd (entlast) tap8))
(setq coords (list 
(list 2560.4549 867.81) 
(list 2560.4449 867.81) 
(list 2560.4448 867.8203) 
(list 2560.4438 867.8306) 
(list 2560.442 867.8408) 
(list 2560.4394 867.8511) 
(list 2560.4362 867.8614) 
(list 2560.4323 867.8717) 
(list 2560.4279 867.8819) 
(list 2560.4231 867.8922) 
(list 2560.418 867.9025) 
(list 2560.4129 867.9128) 
(list 2560.4079 867.9231) 
(list 2560.4031 867.9333) 
(list 2560.3986 867.9436) 
(list 2560.3947 867.9539) 
(list 2560.3915 867.9642) 
(list 2560.389 867.9744) 
(list 2560.3874 867.9847) 
(list 2560.3866 867.995) 
(list 2560.3869 868.0053) 
(list 2560.3881 868.0156) 
(list 2560.3903 868.0258) 
(list 2560.3934 868.0361) 
(list 2560.3973 868.0464) 
(list 2560.4019 868.0567) 
(list 2560.407 868.0669) 
(list 2560.4126 868.0772) 
(list 2560.4185 868.0875) 
(list 2560.4245 868.0978) 
(list 2560.4303 868.1081) 
(list 2560.4359 868.1183) 
(list 2560.441 868.1286) 
(list 2560.4455 868.1389) 
(list 2560.4493 868.1492) 
(list 2560.4522 868.1594) 
(list 2560.454 868.1697) 
(list 2560.4549 868.18) 
(list 2560.4549 868.18)))
(apply 'command (append '("pline") coords '("c")))
(setq tap8 (ssadd (entlast) tap8))
(command "_mirror" (entlast) "" "2560,900" "2560,901" "No")
(setq tap8 (ssadd (entlast) tap8))
(setq coords (list 
(list 2561.129 867.81) 
(list 2560.4549 867.81) 
(list 2560.4549 867.8203) 
(list 2560.4549 867.8306) 
(list 2560.4549 867.8408) 
(list 2560.4549 867.8511) 
(list 2560.4549 867.8614) 
(list 2560.4549 867.8717) 
(list 2560.4549 867.8819) 
(list 2560.4549 867.8922) 
(list 2560.4549 867.9025) 
(list 2560.4549 867.9128) 
(list 2560.4549 867.9231) 
(list 2560.4549 867.9333) 
(list 2560.4549 867.9436) 
(list 2560.4549 867.9539) 
(list 2560.4549 867.9642) 
(list 2560.4549 867.9744) 
(list 2560.4549 867.9847) 
(list 2560.4549 867.995) 
(list 2560.4549 868.0053) 
(list 2560.4549 868.0156) 
(list 2560.4549 868.0258) 
(list 2560.4549 868.0361) 
(list 2560.4549 868.0464) 
(list 2560.4549 868.0567) 
(list 2560.4549 868.0669) 
(list 2560.4549 868.0772) 
(list 2560.4549 868.0875) 
(list 2560.4549 868.0978) 
(list 2560.4549 868.1081) 
(list 2560.4549 868.1183) 
(list 2560.4549 868.1286) 
(list 2560.4549 868.1389) 
(list 2560.4549 868.1492) 
(list 2560.4549 868.1594) 
(list 2560.4549 868.1697) 
(list 2560.4549 868.18) 
(list 2561.129 868.18)))
(apply 'command (append '("pline") coords '("c")))
(setq tap8 (ssadd (entlast) tap8))
(command "_mirror" (entlast) "" "2560,900" "2560,901" "No")
(setq tap8 (ssadd (entlast) tap8))
(setq coords (list 
(list 2560 868.18) 
(list 2560.135 868.18) 
(list 2560.135 868.1903) 
(list 2560.135 868.2006) 
(list 2560.135 868.2108) 
(list 2560.135 868.2211) 
(list 2560.135 868.2314) 
(list 2560.135 868.2417) 
(list 2560.135 868.2519) 
(list 2560.135 868.2622) 
(list 2560.135 868.2725) 
(list 2560.135 868.2828) 
(list 2560.135 868.2931) 
(list 2560.135 868.3033) 
(list 2560.135 868.3136) 
(list 2560.135 868.3239) 
(list 2560.135 868.3342) 
(list 2560.135 868.3444) 
(list 2560.135 868.3547) 
(list 2560.135 868.365) 
(list 2560.135 868.3753) 
(list 2560.135 868.3856) 
(list 2560.135 868.3958) 
(list 2560.135 868.4061) 
(list 2560.135 868.4164) 
(list 2560.135 868.4267) 
(list 2560.135 868.4369) 
(list 2560.135 868.4472) 
(list 2560.135 868.4575) 
(list 2560.135 868.4678) 
(list 2560.135 868.4781) 
(list 2560.135 868.4883) 
(list 2560.135 868.4986) 
(list 2560.135 868.5089) 
(list 2560.135 868.5192) 
(list 2560.135 868.5294) 
(list 2560.135 868.5397) 
(list 2560.135 868.55) 
(list 2560 868.55)))
(apply 'command (append '("pline") coords '("c")))
(setq tap8 (ssadd (entlast) tap8))
(command "_mirror" (entlast) "" "2560,900" "2560,901" "No")
(setq tap8 (ssadd (entlast) tap8))
(setq coords (list 
(list 2560.4648 868.18) 
(list 2560.4549 868.18) 
(list 2560.4546 868.1903) 
(list 2560.4532 868.2006) 
(list 2560.4508 868.2108) 
(list 2560.4473 868.2211) 
(list 2560.4429 868.2314) 
(list 2560.4377 868.2417) 
(list 2560.4319 868.2519) 
(list 2560.4256 868.2622) 
(list 2560.419 868.2725) 
(list 2560.4123 868.2828) 
(list 2560.4057 868.2931) 
(list 2560.3995 868.3033) 
(list 2560.3937 868.3136) 
(list 2560.3887 868.3239) 
(list 2560.3846 868.3342) 
(list 2560.3814 868.3444) 
(list 2560.3794 868.3547) 
(list 2560.3785 868.365) 
(list 2560.3789 868.3753) 
(list 2560.3806 868.3856) 
(list 2560.3834 868.3958) 
(list 2560.3874 868.4061) 
(list 2560.3924 868.4164) 
(list 2560.3983 868.4267) 
(list 2560.4049 868.4369) 
(list 2560.412 868.4472) 
(list 2560.4194 868.4575) 
(list 2560.427 868.4678) 
(list 2560.4343 868.4781) 
(list 2560.4413 868.4883) 
(list 2560.4478 868.4986) 
(list 2560.4534 868.5089) 
(list 2560.4581 868.5192) 
(list 2560.4616 868.5294) 
(list 2560.4639 868.5397) 
(list 2560.4648 868.55) 
(list 2560.4648 868.55)))
(apply 'command (append '("pline") coords '("c")))
(setq tap8 (ssadd (entlast) tap8))
(command "_mirror" (entlast) "" "2560,900" "2560,901" "No")
(setq tap8 (ssadd (entlast) tap8))
(setq coords (list 
(list 2561.129 868.18) 
(list 2560.4648 868.18) 
(list 2560.4648 868.1903) 
(list 2560.4648 868.2006) 
(list 2560.4648 868.2108) 
(list 2560.4648 868.2211) 
(list 2560.4648 868.2314) 
(list 2560.4648 868.2417) 
(list 2560.4648 868.2519) 
(list 2560.4648 868.2622) 
(list 2560.4648 868.2725) 
(list 2560.4648 868.2828) 
(list 2560.4648 868.2931) 
(list 2560.4648 868.3033) 
(list 2560.4648 868.3136) 
(list 2560.4648 868.3239) 
(list 2560.4648 868.3342) 
(list 2560.4648 868.3444) 
(list 2560.4648 868.3547) 
(list 2560.4648 868.365) 
(list 2560.4648 868.3753) 
(list 2560.4648 868.3856) 
(list 2560.4648 868.3958) 
(list 2560.4648 868.4061) 
(list 2560.4648 868.4164) 
(list 2560.4648 868.4267) 
(list 2560.4648 868.4369) 
(list 2560.4648 868.4472) 
(list 2560.4648 868.4575) 
(list 2560.4648 868.4678) 
(list 2560.4648 868.4781) 
(list 2560.4648 868.4883) 
(list 2560.4648 868.4986) 
(list 2560.4648 868.5089) 
(list 2560.4648 868.5192) 
(list 2560.4648 868.5294) 
(list 2560.4648 868.5397) 
(list 2560.4648 868.55) 
(list 2561.129 868.55)))
(apply 'command (append '("pline") coords '("c")))
(setq tap8 (ssadd (entlast) tap8))
(command "_mirror" (entlast) "" "2560,900" "2560,901" "No")
(setq tap8 (ssadd (entlast) tap8))
(setq coords (list 
(list 2560 868.55) 
(list 2560.135 868.55) 
(list 2560.135 868.5603) 
(list 2560.135 868.5706) 
(list 2560.135 868.5808) 
(list 2560.135 868.5911) 
(list 2560.135 868.6014) 
(list 2560.135 868.6117) 
(list 2560.135 868.6219) 
(list 2560.135 868.6322) 
(list 2560.135 868.6425) 
(list 2560.135 868.6528) 
(list 2560.135 868.6631) 
(list 2560.135 868.6733) 
(list 2560.135 868.6836) 
(list 2560.135 868.6939) 
(list 2560.135 868.7042) 
(list 2560.135 868.7144) 
(list 2560.135 868.7247) 
(list 2560.135 868.735) 
(list 2560.135 868.7453) 
(list 2560.135 868.7556) 
(list 2560.135 868.7658) 
(list 2560.135 868.7761) 
(list 2560.135 868.7864) 
(list 2560.135 868.7967) 
(list 2560.135 868.8069) 
(list 2560.135 868.8172) 
(list 2560.135 868.8275) 
(list 2560.135 868.8378) 
(list 2560.135 868.8481) 
(list 2560.135 868.8583) 
(list 2560.135 868.8686) 
(list 2560.135 868.8789) 
(list 2560.135 868.8892) 
(list 2560.135 868.8994) 
(list 2560.135 868.9097) 
(list 2560.135 868.92) 
(list 2560 868.92)))
(apply 'command (append '("pline") coords '("c")))
(setq tap8 (ssadd (entlast) tap8))
(command "_mirror" (entlast) "" "2560,900" "2560,901" "No")
(setq tap8 (ssadd (entlast) tap8))
(setq coords (list 
(list 2560.4748 868.55) 
(list 2560.4648 868.55) 
(list 2560.4644 868.5603) 
(list 2560.4626 868.5706) 
(list 2560.4595 868.5808) 
(list 2560.4551 868.5911) 
(list 2560.4496 868.6014) 
(list 2560.4432 868.6117) 
(list 2560.4359 868.6219) 
(list 2560.4281 868.6322) 
(list 2560.4199 868.6425) 
(list 2560.4116 868.6528) 
(list 2560.4036 868.6631) 
(list 2560.3959 868.6733) 
(list 2560.3889 868.6836) 
(list 2560.3827 868.6939) 
(list 2560.3777 868.7042) 
(list 2560.3739 868.7144) 
(list 2560.3714 868.7247) 
(list 2560.3704 868.735) 
(list 2560.371 868.7453) 
(list 2560.373 868.7556) 
(list 2560.3765 868.7658) 
(list 2560.3814 868.7761) 
(list 2560.3875 868.7864) 
(list 2560.3947 868.7967) 
(list 2560.4027 868.8069) 
(list 2560.4114 868.8172) 
(list 2560.4204 868.8275) 
(list 2560.4295 868.8378) 
(list 2560.4384 868.8481) 
(list 2560.4468 868.8583) 
(list 2560.4545 868.8686) 
(list 2560.4612 868.8789) 
(list 2560.4668 868.8892) 
(list 2560.471 868.8994) 
(list 2560.4737 868.9097) 
(list 2560.4748 868.92) 
(list 2560.4748 868.92)))
(apply 'command (append '("pline") coords '("c")))
(setq tap8 (ssadd (entlast) tap8))
(command "_mirror" (entlast) "" "2560,900" "2560,901" "No")
(setq tap8 (ssadd (entlast) tap8))
(setq coords (list 
(list 2561.129 868.55) 
(list 2560.4748 868.55) 
(list 2560.4748 868.5603) 
(list 2560.4748 868.5706) 
(list 2560.4748 868.5808) 
(list 2560.4748 868.5911) 
(list 2560.4748 868.6014) 
(list 2560.4748 868.6117) 
(list 2560.4748 868.6219) 
(list 2560.4748 868.6322) 
(list 2560.4748 868.6425) 
(list 2560.4748 868.6528) 
(list 2560.4748 868.6631) 
(list 2560.4748 868.6733) 
(list 2560.4748 868.6836) 
(list 2560.4748 868.6939) 
(list 2560.4748 868.7042) 
(list 2560.4748 868.7144) 
(list 2560.4748 868.7247) 
(list 2560.4748 868.735) 
(list 2560.4748 868.7453) 
(list 2560.4748 868.7556) 
(list 2560.4748 868.7658) 
(list 2560.4748 868.7761) 
(list 2560.4748 868.7864) 
(list 2560.4748 868.7967) 
(list 2560.4748 868.8069) 
(list 2560.4748 868.8172) 
(list 2560.4748 868.8275) 
(list 2560.4748 868.8378) 
(list 2560.4748 868.8481) 
(list 2560.4748 868.8583) 
(list 2560.4748 868.8686) 
(list 2560.4748 868.8789) 
(list 2560.4748 868.8892) 
(list 2560.4748 868.8994) 
(list 2560.4748 868.9097) 
(list 2560.4748 868.92) 
(list 2561.129 868.92)))
(apply 'command (append '("pline") coords '("c")))
(setq tap8 (ssadd (entlast) tap8))
(command "_mirror" (entlast) "" "2560,900" "2560,901" "No")
(setq tap8 (ssadd (entlast) tap8))
(setq coords (list 
(list 2560 868.92) 
(list 2560.135 868.92) 
(list 2560.135 868.9303) 
(list 2560.135 868.9406) 
(list 2560.135 868.9508) 
(list 2560.135 868.9611) 
(list 2560.135 868.9714) 
(list 2560.135 868.9817) 
(list 2560.135 868.9919) 
(list 2560.135 869.0022) 
(list 2560.135 869.0125) 
(list 2560.135 869.0228) 
(list 2560.135 869.0331) 
(list 2560.135 869.0433) 
(list 2560.135 869.0536) 
(list 2560.135 869.0639) 
(list 2560.135 869.0742) 
(list 2560.135 869.0844) 
(list 2560.135 869.0947) 
(list 2560.135 869.105) 
(list 2560.135 869.1153) 
(list 2560.135 869.1256) 
(list 2560.135 869.1358) 
(list 2560.135 869.1461) 
(list 2560.135 869.1564) 
(list 2560.135 869.1667) 
(list 2560.135 869.1769) 
(list 2560.135 869.1872) 
(list 2560.135 869.1975) 
(list 2560.135 869.2078) 
(list 2560.135 869.2181) 
(list 2560.135 869.2283) 
(list 2560.135 869.2386) 
(list 2560.135 869.2489) 
(list 2560.135 869.2592) 
(list 2560.135 869.2694) 
(list 2560.135 869.2797) 
(list 2560.135 869.29) 
(list 2560 869.29)))
(apply 'command (append '("pline") coords '("c")))
(setq tap8 (ssadd (entlast) tap8))
(command "_mirror" (entlast) "" "2560,900" "2560,901" "No")
(setq tap8 (ssadd (entlast) tap8))
(setq coords (list 
(list 2560.4848 868.92) 
(list 2560.4748 868.92) 
(list 2560.4742 868.9303) 
(list 2560.4721 868.9406) 
(list 2560.4683 868.9508) 
(list 2560.463 868.9611) 
(list 2560.4564 868.9714) 
(list 2560.4486 868.9817) 
(list 2560.4399 868.9919) 
(list 2560.4306 869.0022) 
(list 2560.4208 869.0125) 
(list 2560.411 869.0228) 
(list 2560.4014 869.0331) 
(list 2560.3923 869.0433) 
(list 2560.384 869.0536) 
(list 2560.3768 869.0639) 
(list 2560.3708 869.0742) 
(list 2560.3663 869.0844) 
(list 2560.3635 869.0947) 
(list 2560.3623 869.105) 
(list 2560.363 869.1153) 
(list 2560.3655 869.1256) 
(list 2560.3696 869.1358) 
(list 2560.3754 869.1461) 
(list 2560.3826 869.1564) 
(list 2560.3911 869.1667) 
(list 2560.4006 869.1769) 
(list 2560.4107 869.1872) 
(list 2560.4213 869.1975) 
(list 2560.432 869.2078) 
(list 2560.4424 869.2181) 
(list 2560.4522 869.2283) 
(list 2560.4612 869.2386) 
(list 2560.4691 869.2489) 
(list 2560.4756 869.2592) 
(list 2560.4804 869.2694) 
(list 2560.4835 869.2797) 
(list 2560.4848 869.29) 
(list 2560.4848 869.29)))
(apply 'command (append '("pline") coords '("c")))
(setq tap8 (ssadd (entlast) tap8))
(command "_mirror" (entlast) "" "2560,900" "2560,901" "No")
(setq tap8 (ssadd (entlast) tap8))
(setq coords (list 
(list 2561.129 868.92) 
(list 2560.4848 868.92) 
(list 2560.4848 868.9303) 
(list 2560.4848 868.9406) 
(list 2560.4848 868.9508) 
(list 2560.4848 868.9611) 
(list 2560.4848 868.9714) 
(list 2560.4848 868.9817) 
(list 2560.4848 868.9919) 
(list 2560.4848 869.0022) 
(list 2560.4848 869.0125) 
(list 2560.4848 869.0228) 
(list 2560.4848 869.0331) 
(list 2560.4848 869.0433) 
(list 2560.4848 869.0536) 
(list 2560.4848 869.0639) 
(list 2560.4848 869.0742) 
(list 2560.4848 869.0844) 
(list 2560.4848 869.0947) 
(list 2560.4848 869.105) 
(list 2560.4848 869.1153) 
(list 2560.4848 869.1256) 
(list 2560.4848 869.1358) 
(list 2560.4848 869.1461) 
(list 2560.4848 869.1564) 
(list 2560.4848 869.1667) 
(list 2560.4848 869.1769) 
(list 2560.4848 869.1872) 
(list 2560.4848 869.1975) 
(list 2560.4848 869.2078) 
(list 2560.4848 869.2181) 
(list 2560.4848 869.2283) 
(list 2560.4848 869.2386) 
(list 2560.4848 869.2489) 
(list 2560.4848 869.2592) 
(list 2560.4848 869.2694) 
(list 2560.4848 869.2797) 
(list 2560.4848 869.29) 
(list 2561.129 869.29)))
(apply 'command (append '("pline") coords '("c")))
(setq tap8 (ssadd (entlast) tap8))
(command "_mirror" (entlast) "" "2560,900" "2560,901" "No")
(setq tap8 (ssadd (entlast) tap8))
(setq coords (list 
(list 2560 869.29) 
(list 2560.135 869.29) 
(list 2560.135 869.3003) 
(list 2560.135 869.3106) 
(list 2560.135 869.3208) 
(list 2560.135 869.3311) 
(list 2560.135 869.3414) 
(list 2560.135 869.3517) 
(list 2560.135 869.3619) 
(list 2560.135 869.3722) 
(list 2560.135 869.3825) 
(list 2560.135 869.3928) 
(list 2560.135 869.4031) 
(list 2560.135 869.4133) 
(list 2560.135 869.4236) 
(list 2560.135 869.4339) 
(list 2560.135 869.4442) 
(list 2560.135 869.4544) 
(list 2560.135 869.4647) 
(list 2560.135 869.475) 
(list 2560.135 869.4853) 
(list 2560.135 869.4956) 
(list 2560.135 869.5058) 
(list 2560.135 869.5161) 
(list 2560.135 869.5264) 
(list 2560.135 869.5367) 
(list 2560.135 869.5469) 
(list 2560.135 869.5572) 
(list 2560.135 869.5675) 
(list 2560.135 869.5778) 
(list 2560.135 869.5881) 
(list 2560.135 869.5983) 
(list 2560.135 869.6086) 
(list 2560.135 869.6189) 
(list 2560.135 869.6292) 
(list 2560.135 869.6394) 
(list 2560.135 869.6497) 
(list 2560.135 869.66) 
(list 2560 869.66)))
(apply 'command (append '("pline") coords '("c")))
(setq tap8 (ssadd (entlast) tap8))
(command "_mirror" (entlast) "" "2560,900" "2560,901" "No")
(setq tap8 (ssadd (entlast) tap8))
(setq coords (list 
(list 2560.4947 869.29) 
(list 2560.4848 869.29) 
(list 2560.4841 869.3003) 
(list 2560.4815 869.3106) 
(list 2560.477 869.3208) 
(list 2560.4708 869.3311) 
(list 2560.4631 869.3414) 
(list 2560.4541 869.3517) 
(list 2560.4439 869.3619) 
(list 2560.4331 869.3722) 
(list 2560.4218 869.3825) 
(list 2560.4104 869.3928) 
(list 2560.3992 869.4031) 
(list 2560.3887 869.4133) 
(list 2560.3791 869.4236) 
(list 2560.3708 869.4339) 
(list 2560.3639 869.4442) 
(list 2560.3588 869.4544) 
(list 2560.3555 869.4647) 
(list 2560.3542 869.475) 
(list 2560.3551 869.4853) 
(list 2560.3579 869.4956) 
(list 2560.3628 869.5058) 
(list 2560.3694 869.5161) 
(list 2560.3778 869.5264) 
(list 2560.3875 869.5367) 
(list 2560.3984 869.5469) 
(list 2560.4101 869.5572) 
(list 2560.4222 869.5675) 
(list 2560.4345 869.5778) 
(list 2560.4464 869.5881) 
(list 2560.4577 869.5983) 
(list 2560.468 869.6086) 
(list 2560.477 869.6189) 
(list 2560.4843 869.6292) 
(list 2560.4899 869.6394) 
(list 2560.4934 869.6497) 
(list 2560.4947 869.66) 
(list 2560.4947 869.66)))
(apply 'command (append '("pline") coords '("c")))
(setq tap8 (ssadd (entlast) tap8))
(command "_mirror" (entlast) "" "2560,900" "2560,901" "No")
(setq tap8 (ssadd (entlast) tap8))
(setq coords (list 
(list 2561.129 869.29) 
(list 2560.4947 869.29) 
(list 2560.4947 869.3003) 
(list 2560.4947 869.3106) 
(list 2560.4947 869.3208) 
(list 2560.4947 869.3311) 
(list 2560.4947 869.3414) 
(list 2560.4947 869.3517) 
(list 2560.4947 869.3619) 
(list 2560.4947 869.3722) 
(list 2560.4947 869.3825) 
(list 2560.4947 869.3928) 
(list 2560.4947 869.4031) 
(list 2560.4947 869.4133) 
(list 2560.4947 869.4236) 
(list 2560.4947 869.4339) 
(list 2560.4947 869.4442) 
(list 2560.4947 869.4544) 
(list 2560.4947 869.4647) 
(list 2560.4947 869.475) 
(list 2560.4947 869.4853) 
(list 2560.4947 869.4956) 
(list 2560.4947 869.5058) 
(list 2560.4947 869.5161) 
(list 2560.4947 869.5264) 
(list 2560.4947 869.5367) 
(list 2560.4947 869.5469) 
(list 2560.4947 869.5572) 
(list 2560.4947 869.5675) 
(list 2560.4947 869.5778) 
(list 2560.4947 869.5881) 
(list 2560.4947 869.5983) 
(list 2560.4947 869.6086) 
(list 2560.4947 869.6189) 
(list 2560.4947 869.6292) 
(list 2560.4947 869.6394) 
(list 2560.4947 869.6497) 
(list 2560.4947 869.66) 
(list 2561.129 869.66)))
(apply 'command (append '("pline") coords '("c")))
(setq tap8 (ssadd (entlast) tap8))
(command "_mirror" (entlast) "" "2560,900" "2560,901" "No")
(setq tap8 (ssadd (entlast) tap8))
(setq coords (list 
(list 2560 869.66) 
(list 2560.135 869.66) 
(list 2560.135 869.6703) 
(list 2560.135 869.6806) 
(list 2560.135 869.6908) 
(list 2560.135 869.7011) 
(list 2560.135 869.7114) 
(list 2560.135 869.7217) 
(list 2560.135 869.7319) 
(list 2560.135 869.7422) 
(list 2560.135 869.7525) 
(list 2560.135 869.7628) 
(list 2560.135 869.7731) 
(list 2560.135 869.7833) 
(list 2560.135 869.7936) 
(list 2560.135 869.8039) 
(list 2560.135 869.8142) 
(list 2560.135 869.8244) 
(list 2560.135 869.8347) 
(list 2560.135 869.845) 
(list 2560.135 869.8553) 
(list 2560.135 869.8656) 
(list 2560.135 869.8758) 
(list 2560.135 869.8861) 
(list 2560.135 869.8964) 
(list 2560.135 869.9067) 
(list 2560.135 869.9169) 
(list 2560.135 869.9272) 
(list 2560.135 869.9375) 
(list 2560.135 869.9478) 
(list 2560.135 869.9581) 
(list 2560.135 869.9683) 
(list 2560.135 869.9786) 
(list 2560.135 869.9889) 
(list 2560.135 869.9992) 
(list 2560.135 870.0094) 
(list 2560.135 870.0197) 
(list 2560.135 870.03) 
(list 2560 870.03)))
(apply 'command (append '("pline") coords '("c")))
(setq tap8 (ssadd (entlast) tap8))
(command "_mirror" (entlast) "" "2560,900" "2560,901" "No")
(setq tap8 (ssadd (entlast) tap8))
(setq coords (list 
(list 2560.5047 869.66) 
(list 2560.4947 869.66) 
(list 2560.4939 869.6703) 
(list 2560.4909 869.6806) 
(list 2560.4858 869.6908) 
(list 2560.4787 869.7011) 
(list 2560.4699 869.7114) 
(list 2560.4595 869.7217) 
(list 2560.448 869.7319) 
(list 2560.4356 869.7422) 
(list 2560.4227 869.7525) 
(list 2560.4097 869.7628) 
(list 2560.3971 869.7731) 
(list 2560.3851 869.7833) 
(list 2560.3743 869.7936) 
(list 2560.3648 869.8039) 
(list 2560.357 869.8142) 
(list 2560.3512 869.8244) 
(list 2560.3475 869.8347) 
(list 2560.3461 869.845) 
(list 2560.3471 869.8553) 
(list 2560.3504 869.8656) 
(list 2560.3559 869.8758) 
(list 2560.3634 869.8861) 
(list 2560.3729 869.8964) 
(list 2560.3839 869.9067) 
(list 2560.3963 869.9169) 
(list 2560.4095 869.9272) 
(list 2560.4232 869.9375) 
(list 2560.437 869.9478) 
(list 2560.4504 869.9581) 
(list 2560.4631 869.9683) 
(list 2560.4747 869.9786) 
(list 2560.4848 869.9889) 
(list 2560.4931 869.9992) 
(list 2560.4993 870.0094) 
(list 2560.5032 870.0197) 
(list 2560.5047 870.03) 
(list 2560.5047 870.03)))
(apply 'command (append '("pline") coords '("c")))
(setq tap8 (ssadd (entlast) tap8))
(command "_mirror" (entlast) "" "2560,900" "2560,901" "No")
(setq tap8 (ssadd (entlast) tap8))
(setq coords (list 
(list 2561.129 869.66) 
(list 2560.5047 869.66) 
(list 2560.5047 869.6703) 
(list 2560.5047 869.6806) 
(list 2560.5047 869.6908) 
(list 2560.5047 869.7011) 
(list 2560.5047 869.7114) 
(list 2560.5047 869.7217) 
(list 2560.5047 869.7319) 
(list 2560.5047 869.7422) 
(list 2560.5047 869.7525) 
(list 2560.5047 869.7628) 
(list 2560.5047 869.7731) 
(list 2560.5047 869.7833) 
(list 2560.5047 869.7936) 
(list 2560.5047 869.8039) 
(list 2560.5047 869.8142) 
(list 2560.5047 869.8244) 
(list 2560.5047 869.8347) 
(list 2560.5047 869.845) 
(list 2560.5047 869.8553) 
(list 2560.5047 869.8656) 
(list 2560.5047 869.8758) 
(list 2560.5047 869.8861) 
(list 2560.5047 869.8964) 
(list 2560.5047 869.9067) 
(list 2560.5047 869.9169) 
(list 2560.5047 869.9272) 
(list 2560.5047 869.9375) 
(list 2560.5047 869.9478) 
(list 2560.5047 869.9581) 
(list 2560.5047 869.9683) 
(list 2560.5047 869.9786) 
(list 2560.5047 869.9889) 
(list 2560.5047 869.9992) 
(list 2560.5047 870.0094) 
(list 2560.5047 870.0197) 
(list 2560.5047 870.03) 
(list 2561.129 870.03)))
(apply 'command (append '("pline") coords '("c")))
(setq tap8 (ssadd (entlast) tap8))
(command "_mirror" (entlast) "" "2560,900" "2560,901" "No")
(setq tap8 (ssadd (entlast) tap8))
(setq coords (list 
(list 2560 870.03) 
(list 2560.135 870.03) 
(list 2560.135 870.0403) 
(list 2560.135 870.0506) 
(list 2560.135 870.0608) 
(list 2560.135 870.0711) 
(list 2560.135 870.0814) 
(list 2560.135 870.0917) 
(list 2560.135 870.1019) 
(list 2560.135 870.1122) 
(list 2560.135 870.1225) 
(list 2560.135 870.1328) 
(list 2560.135 870.1431) 
(list 2560.135 870.1533) 
(list 2560.135 870.1636) 
(list 2560.135 870.1739) 
(list 2560.135 870.1842) 
(list 2560.135 870.1944) 
(list 2560.135 870.2047) 
(list 2560.135 870.215) 
(list 2560.135 870.2253) 
(list 2560.135 870.2356) 
(list 2560.135 870.2458) 
(list 2560.135 870.2561) 
(list 2560.135 870.2664) 
(list 2560.135 870.2767) 
(list 2560.135 870.2869) 
(list 2560.135 870.2972) 
(list 2560.135 870.3075) 
(list 2560.135 870.3178) 
(list 2560.135 870.3281) 
(list 2560.135 870.3383) 
(list 2560.135 870.3486) 
(list 2560.135 870.3589) 
(list 2560.135 870.3692) 
(list 2560.135 870.3794) 
(list 2560.135 870.3897) 
(list 2560.135 870.4) 
(list 2560 870.4)))
(apply 'command (append '("pline") coords '("c")))
(setq tap8 (ssadd (entlast) tap8))
(command "_mirror" (entlast) "" "2560,900" "2560,901" "No")
(setq tap8 (ssadd (entlast) tap8))
(setq coords (list 
(list 2560.5147 870.03) 
(list 2560.5047 870.03) 
(list 2560.5037 870.0403) 
(list 2560.5003 870.0506) 
(list 2560.4945 870.0608) 
(list 2560.4866 870.0711) 
(list 2560.4766 870.0814) 
(list 2560.465 870.0917) 
(list 2560.452 870.1019) 
(list 2560.4381 870.1122) 
(list 2560.4236 870.1225) 
(list 2560.4091 870.1328) 
(list 2560.3949 870.1431) 
(list 2560.3816 870.1533) 
(list 2560.3694 870.1636) 
(list 2560.3588 870.1739) 
(list 2560.3501 870.1842) 
(list 2560.3436 870.1944) 
(list 2560.3396 870.2047) 
(list 2560.338 870.215) 
(list 2560.3391 870.2253) 
(list 2560.3428 870.2356) 
(list 2560.349 870.2458) 
(list 2560.3575 870.2561) 
(list 2560.368 870.2664) 
(list 2560.3804 870.2767) 
(list 2560.3941 870.2869) 
(list 2560.4088 870.2972) 
(list 2560.4241 870.3075) 
(list 2560.4395 870.3178) 
(list 2560.4544 870.3281) 
(list 2560.4686 870.3383) 
(list 2560.4815 870.3486) 
(list 2560.4927 870.3589) 
(list 2560.5018 870.3692) 
(list 2560.5087 870.3794) 
(list 2560.513 870.3897) 
(list 2560.5147 870.4) 
(list 2560.5147 870.4)))
(apply 'command (append '("pline") coords '("c")))
(setq tap8 (ssadd (entlast) tap8))
(command "_mirror" (entlast) "" "2560,900" "2560,901" "No")
(setq tap8 (ssadd (entlast) tap8))
(setq coords (list 
(list 2561.129 870.03) 
(list 2560.5147 870.03) 
(list 2560.5147 870.0403) 
(list 2560.5147 870.0506) 
(list 2560.5147 870.0608) 
(list 2560.5147 870.0711) 
(list 2560.5147 870.0814) 
(list 2560.5147 870.0917) 
(list 2560.5147 870.1019) 
(list 2560.5147 870.1122) 
(list 2560.5147 870.1225) 
(list 2560.5147 870.1328) 
(list 2560.5147 870.1431) 
(list 2560.5147 870.1533) 
(list 2560.5147 870.1636) 
(list 2560.5147 870.1739) 
(list 2560.5147 870.1842) 
(list 2560.5147 870.1944) 
(list 2560.5147 870.2047) 
(list 2560.5147 870.215) 
(list 2560.5147 870.2253) 
(list 2560.5147 870.2356) 
(list 2560.5147 870.2458) 
(list 2560.5147 870.2561) 
(list 2560.5147 870.2664) 
(list 2560.5147 870.2767) 
(list 2560.5147 870.2869) 
(list 2560.5147 870.2972) 
(list 2560.5147 870.3075) 
(list 2560.5147 870.3178) 
(list 2560.5147 870.3281) 
(list 2560.5147 870.3383) 
(list 2560.5147 870.3486) 
(list 2560.5147 870.3589) 
(list 2560.5147 870.3692) 
(list 2560.5147 870.3794) 
(list 2560.5147 870.3897) 
(list 2560.5147 870.4) 
(list 2561.129 870.4)))
(apply 'command (append '("pline") coords '("c")))
(setq tap8 (ssadd (entlast) tap8))
(command "_mirror" (entlast) "" "2560,900" "2560,901" "No")
(setq tap8 (ssadd (entlast) tap8))
(setq coords (list 
(list 2560 870.4) 
(list 2560.135 870.4) 
(list 2560.135 870.4103) 
(list 2560.135 870.4206) 
(list 2560.135 870.4308) 
(list 2560.135 870.4411) 
(list 2560.135 870.4514) 
(list 2560.135 870.4617) 
(list 2560.135 870.4719) 
(list 2560.135 870.4822) 
(list 2560.135 870.4925) 
(list 2560.135 870.5028) 
(list 2560.135 870.5131) 
(list 2560.135 870.5233) 
(list 2560.135 870.5336) 
(list 2560.135 870.5439) 
(list 2560.135 870.5542) 
(list 2560.135 870.5644) 
(list 2560.135 870.5747) 
(list 2560.135 870.585) 
(list 2560.135 870.5953) 
(list 2560.135 870.6056) 
(list 2560.135 870.6158) 
(list 2560.135 870.6261) 
(list 2560.135 870.6364) 
(list 2560.135 870.6467) 
(list 2560.135 870.6569) 
(list 2560.135 870.6672) 
(list 2560.135 870.6775) 
(list 2560.135 870.6878) 
(list 2560.135 870.6981) 
(list 2560.135 870.7083) 
(list 2560.135 870.7186) 
(list 2560.135 870.7289) 
(list 2560.135 870.7392) 
(list 2560.135 870.7494) 
(list 2560.135 870.7597) 
(list 2560.135 870.77) 
(list 2560 870.77)))
(apply 'command (append '("pline") coords '("c")))
(setq tap8 (ssadd (entlast) tap8))
(command "_mirror" (entlast) "" "2560,900" "2560,901" "No")
(setq tap8 (ssadd (entlast) tap8))
(setq coords (list 
(list 2560.5246 870.4) 
(list 2560.5147 870.4) 
(list 2560.5136 870.4103) 
(list 2560.5097 870.4206) 
(list 2560.5033 870.4308) 
(list 2560.4944 870.4411) 
(list 2560.4833 870.4514) 
(list 2560.4704 870.4617) 
(list 2560.456 870.4719) 
(list 2560.4406 870.4822) 
(list 2560.4246 870.4925) 
(list 2560.4085 870.5028) 
(list 2560.3928 870.5131) 
(list 2560.378 870.5233) 
(list 2560.3645 870.5336) 
(list 2560.3528 870.5439) 
(list 2560.3432 870.5542) 
(list 2560.3361 870.5644) 
(list 2560.3316 870.5747) 
(list 2560.3299 870.585) 
(list 2560.3312 870.5953) 
(list 2560.3353 870.6056) 
(list 2560.3421 870.6158) 
(list 2560.3515 870.6261) 
(list 2560.3632 870.6364) 
(list 2560.3768 870.6467) 
(list 2560.3919 870.6569) 
(list 2560.4082 870.6672) 
(list 2560.425 870.6775) 
(list 2560.442 870.6878) 
(list 2560.4585 870.6981) 
(list 2560.474 870.7083) 
(list 2560.4882 870.7186) 
(list 2560.5005 870.7289) 
(list 2560.5106 870.7392) 
(list 2560.5181 870.7494) 
(list 2560.5228 870.7597) 
(list 2560.5246 870.77) 
(list 2560.5246 870.77)))
(apply 'command (append '("pline") coords '("c")))
(setq tap8 (ssadd (entlast) tap8))
(command "_mirror" (entlast) "" "2560,900" "2560,901" "No")
(setq tap8 (ssadd (entlast) tap8))
(setq coords (list 
(list 2561.129 870.4) 
(list 2560.5246 870.4) 
(list 2560.5246 870.4103) 
(list 2560.5246 870.4206) 
(list 2560.5246 870.4308) 
(list 2560.5246 870.4411) 
(list 2560.5246 870.4514) 
(list 2560.5246 870.4617) 
(list 2560.5246 870.4719) 
(list 2560.5246 870.4822) 
(list 2560.5246 870.4925) 
(list 2560.5246 870.5028) 
(list 2560.5246 870.5131) 
(list 2560.5246 870.5233) 
(list 2560.5246 870.5336) 
(list 2560.5246 870.5439) 
(list 2560.5246 870.5542) 
(list 2560.5246 870.5644) 
(list 2560.5246 870.5747) 
(list 2560.5246 870.585) 
(list 2560.5246 870.5953) 
(list 2560.5246 870.6056) 
(list 2560.5246 870.6158) 
(list 2560.5246 870.6261) 
(list 2560.5246 870.6364) 
(list 2560.5246 870.6467) 
(list 2560.5246 870.6569) 
(list 2560.5246 870.6672) 
(list 2560.5246 870.6775) 
(list 2560.5246 870.6878) 
(list 2560.5246 870.6981) 
(list 2560.5246 870.7083) 
(list 2560.5246 870.7186) 
(list 2560.5246 870.7289) 
(list 2560.5246 870.7392) 
(list 2560.5246 870.7494) 
(list 2560.5246 870.7597) 
(list 2560.5246 870.77) 
(list 2561.129 870.77)))
(apply 'command (append '("pline") coords '("c")))
(setq tap8 (ssadd (entlast) tap8))
(command "_mirror" (entlast) "" "2560,900" "2560,901" "No")
(setq tap8 (ssadd (entlast) tap8))
(setq coords (list 
(list 2560 870.77) 
(list 2560.135 870.77) 
(list 2560.135 870.7803) 
(list 2560.135 870.7906) 
(list 2560.135 870.8008) 
(list 2560.135 870.8111) 
(list 2560.135 870.8214) 
(list 2560.135 870.8317) 
(list 2560.135 870.8419) 
(list 2560.135 870.8522) 
(list 2560.135 870.8625) 
(list 2560.135 870.8728) 
(list 2560.135 870.8831) 
(list 2560.135 870.8933) 
(list 2560.135 870.9036) 
(list 2560.135 870.9139) 
(list 2560.135 870.9242) 
(list 2560.135 870.9344) 
(list 2560.135 870.9447) 
(list 2560.135 870.955) 
(list 2560.135 870.9653) 
(list 2560.135 870.9756) 
(list 2560.135 870.9858) 
(list 2560.135 870.9961) 
(list 2560.135 871.0064) 
(list 2560.135 871.0167) 
(list 2560.135 871.0269) 
(list 2560.135 871.0372) 
(list 2560.135 871.0475) 
(list 2560.135 871.0578) 
(list 2560.135 871.0681) 
(list 2560.135 871.0783) 
(list 2560.135 871.0886) 
(list 2560.135 871.0989) 
(list 2560.135 871.1092) 
(list 2560.135 871.1194) 
(list 2560.135 871.1297) 
(list 2560.135 871.14) 
(list 2560 871.14)))
(apply 'command (append '("pline") coords '("c")))
(setq tap8 (ssadd (entlast) tap8))
(command "_mirror" (entlast) "" "2560,900" "2560,901" "No")
(setq tap8 (ssadd (entlast) tap8))
(setq coords (list 
(list 2560.5346 870.77) 
(list 2560.5246 870.77) 
(list 2560.5234 870.7803) 
(list 2560.5192 870.7906) 
(list 2560.512 870.8008) 
(list 2560.5023 870.8111) 
(list 2560.4901 870.8214) 
(list 2560.4759 870.8317) 
(list 2560.46 870.8419) 
(list 2560.4431 870.8522) 
(list 2560.4255 870.8625) 
(list 2560.4078 870.8728) 
(list 2560.3906 870.8831) 
(list 2560.3744 870.8933) 
(list 2560.3596 870.9036) 
(list 2560.3468 870.9139) 
(list 2560.3363 870.9242) 
(list 2560.3285 870.9344) 
(list 2560.3236 870.9447) 
(list 2560.3218 870.955) 
(list 2560.3232 870.9653) 
(list 2560.3277 870.9756) 
(list 2560.3352 870.9858) 
(list 2560.3455 870.9961) 
(list 2560.3583 871.0064) 
(list 2560.3732 871.0167) 
(list 2560.3898 871.0269) 
(list 2560.4076 871.0372) 
(list 2560.426 871.0475) 
(list 2560.4445 871.0578) 
(list 2560.4625 871.0681) 
(list 2560.4795 871.0783) 
(list 2560.4949 871.0886) 
(list 2560.5084 871.0989) 
(list 2560.5193 871.1092) 
(list 2560.5275 871.1194) 
(list 2560.5327 871.1297) 
(list 2560.5346 871.14) 
(list 2560.5346 871.14)))
(apply 'command (append '("pline") coords '("c")))
(setq tap8 (ssadd (entlast) tap8))
(command "_mirror" (entlast) "" "2560,900" "2560,901" "No")
(setq tap8 (ssadd (entlast) tap8))
(setq coords (list 
(list 2561.129 870.77) 
(list 2560.5346 870.77) 
(list 2560.5346 870.7803) 
(list 2560.5346 870.7906) 
(list 2560.5346 870.8008) 
(list 2560.5346 870.8111) 
(list 2560.5346 870.8214) 
(list 2560.5346 870.8317) 
(list 2560.5346 870.8419) 
(list 2560.5346 870.8522) 
(list 2560.5346 870.8625) 
(list 2560.5346 870.8728) 
(list 2560.5346 870.8831) 
(list 2560.5346 870.8933) 
(list 2560.5346 870.9036) 
(list 2560.5346 870.9139) 
(list 2560.5346 870.9242) 
(list 2560.5346 870.9344) 
(list 2560.5346 870.9447) 
(list 2560.5346 870.955) 
(list 2560.5346 870.9653) 
(list 2560.5346 870.9756) 
(list 2560.5346 870.9858) 
(list 2560.5346 870.9961) 
(list 2560.5346 871.0064) 
(list 2560.5346 871.0167) 
(list 2560.5346 871.0269) 
(list 2560.5346 871.0372) 
(list 2560.5346 871.0475) 
(list 2560.5346 871.0578) 
(list 2560.5346 871.0681) 
(list 2560.5346 871.0783) 
(list 2560.5346 871.0886) 
(list 2560.5346 871.0989) 
(list 2560.5346 871.1092) 
(list 2560.5346 871.1194) 
(list 2560.5346 871.1297) 
(list 2560.5346 871.14) 
(list 2561.129 871.14)))
(apply 'command (append '("pline") coords '("c")))
(setq tap8 (ssadd (entlast) tap8))
(command "_mirror" (entlast) "" "2560,900" "2560,901" "No")
(setq tap8 (ssadd (entlast) tap8))
(setq coords (list 
(list 2560 871.14) 
(list 2560.135 871.14) 
(list 2560.135 871.1503) 
(list 2560.135 871.1606) 
(list 2560.135 871.1708) 
(list 2560.135 871.1811) 
(list 2560.135 871.1914) 
(list 2560.135 871.2017) 
(list 2560.135 871.2119) 
(list 2560.135 871.2222) 
(list 2560.135 871.2325) 
(list 2560.135 871.2428) 
(list 2560.135 871.2531) 
(list 2560.135 871.2633) 
(list 2560.135 871.2736) 
(list 2560.135 871.2839) 
(list 2560.135 871.2942) 
(list 2560.135 871.3044) 
(list 2560.135 871.3147) 
(list 2560.135 871.325) 
(list 2560.135 871.3353) 
(list 2560.135 871.3456) 
(list 2560.135 871.3558) 
(list 2560.135 871.3661) 
(list 2560.135 871.3764) 
(list 2560.135 871.3867) 
(list 2560.135 871.3969) 
(list 2560.135 871.4072) 
(list 2560.135 871.4175) 
(list 2560.135 871.4278) 
(list 2560.135 871.4381) 
(list 2560.135 871.4483) 
(list 2560.135 871.4586) 
(list 2560.135 871.4689) 
(list 2560.135 871.4792) 
(list 2560.135 871.4894) 
(list 2560.135 871.4997) 
(list 2560.135 871.51) 
(list 2560 871.51)))
(apply 'command (append '("pline") coords '("c")))
(setq tap8 (ssadd (entlast) tap8))
(command "_mirror" (entlast) "" "2560,900" "2560,901" "No")
(setq tap8 (ssadd (entlast) tap8))
(setq coords (list 
(list 2560.5446 871.14) 
(list 2560.5346 871.14) 
(list 2560.5332 871.1503) 
(list 2560.5286 871.1606) 
(list 2560.5208 871.1708) 
(list 2560.5101 871.1811) 
(list 2560.4968 871.1914) 
(list 2560.4813 871.2017) 
(list 2560.4641 871.2119) 
(list 2560.4456 871.2222) 
(list 2560.4264 871.2325) 
(list 2560.4072 871.2428) 
(list 2560.3885 871.2531) 
(list 2560.3708 871.2633) 
(list 2560.3548 871.2736) 
(list 2560.3408 871.2839) 
(list 2560.3295 871.2942) 
(list 2560.321 871.3044) 
(list 2560.3157 871.3147) 
(list 2560.3137 871.325) 
(list 2560.3152 871.3353) 
(list 2560.3201 871.3456) 
(list 2560.3283 871.3558) 
(list 2560.3395 871.3661) 
(list 2560.3534 871.3764) 
(list 2560.3696 871.3867) 
(list 2560.3876 871.3969) 
(list 2560.4069 871.4072) 
(list 2560.4269 871.4175) 
(list 2560.447 871.4278) 
(list 2560.4665 871.4381) 
(list 2560.4849 871.4483) 
(list 2560.5017 871.4586) 
(list 2560.5162 871.4689) 
(list 2560.5281 871.4792) 
(list 2560.537 871.4894) 
(list 2560.5425 871.4997) 
(list 2560.5446 871.51) 
(list 2560.5446 871.51)))
(apply 'command (append '("pline") coords '("c")))
(setq tap8 (ssadd (entlast) tap8))
(command "_mirror" (entlast) "" "2560,900" "2560,901" "No")
(setq tap8 (ssadd (entlast) tap8))
(setq coords (list 
(list 2561.129 871.14) 
(list 2560.5446 871.14) 
(list 2560.5446 871.1503) 
(list 2560.5446 871.1606) 
(list 2560.5446 871.1708) 
(list 2560.5446 871.1811) 
(list 2560.5446 871.1914) 
(list 2560.5446 871.2017) 
(list 2560.5446 871.2119) 
(list 2560.5446 871.2222) 
(list 2560.5446 871.2325) 
(list 2560.5446 871.2428) 
(list 2560.5446 871.2531) 
(list 2560.5446 871.2633) 
(list 2560.5446 871.2736) 
(list 2560.5446 871.2839) 
(list 2560.5446 871.2942) 
(list 2560.5446 871.3044) 
(list 2560.5446 871.3147) 
(list 2560.5446 871.325) 
(list 2560.5446 871.3353) 
(list 2560.5446 871.3456) 
(list 2560.5446 871.3558) 
(list 2560.5446 871.3661) 
(list 2560.5446 871.3764) 
(list 2560.5446 871.3867) 
(list 2560.5446 871.3969) 
(list 2560.5446 871.4072) 
(list 2560.5446 871.4175) 
(list 2560.5446 871.4278) 
(list 2560.5446 871.4381) 
(list 2560.5446 871.4483) 
(list 2560.5446 871.4586) 
(list 2560.5446 871.4689) 
(list 2560.5446 871.4792) 
(list 2560.5446 871.4894) 
(list 2560.5446 871.4997) 
(list 2560.5446 871.51) 
(list 2561.129 871.51)))
(apply 'command (append '("pline") coords '("c")))
(setq tap8 (ssadd (entlast) tap8))
(command "_mirror" (entlast) "" "2560,900" "2560,901" "No")
(setq tap8 (ssadd (entlast) tap8))
(setq coords (list 
(list 2560 871.51) 
(list 2560.135 871.51) 
(list 2560.135 871.5203) 
(list 2560.135 871.5306) 
(list 2560.135 871.5408) 
(list 2560.135 871.5511) 
(list 2560.135 871.5614) 
(list 2560.135 871.5717) 
(list 2560.135 871.5819) 
(list 2560.135 871.5922) 
(list 2560.135 871.6025) 
(list 2560.135 871.6128) 
(list 2560.135 871.6231) 
(list 2560.135 871.6333) 
(list 2560.135 871.6436) 
(list 2560.135 871.6539) 
(list 2560.135 871.6642) 
(list 2560.135 871.6744) 
(list 2560.135 871.6847) 
(list 2560.135 871.695) 
(list 2560.135 871.7053) 
(list 2560.135 871.7156) 
(list 2560.135 871.7258) 
(list 2560.135 871.7361) 
(list 2560.135 871.7464) 
(list 2560.135 871.7567) 
(list 2560.135 871.7669) 
(list 2560.135 871.7772) 
(list 2560.135 871.7875) 
(list 2560.135 871.7978) 
(list 2560.135 871.8081) 
(list 2560.135 871.8183) 
(list 2560.135 871.8286) 
(list 2560.135 871.8389) 
(list 2560.135 871.8492) 
(list 2560.135 871.8594) 
(list 2560.135 871.8697) 
(list 2560.135 871.88) 
(list 2560 871.88)))
(apply 'command (append '("pline") coords '("c")))
(setq tap8 (ssadd (entlast) tap8))
(command "_mirror" (entlast) "" "2560,900" "2560,901" "No")
(setq tap8 (ssadd (entlast) tap8))
(setq coords (list 
(list 2560.5545 871.51) 
(list 2560.5446 871.51) 
(list 2560.5431 871.5203) 
(list 2560.538 871.5306) 
(list 2560.5296 871.5408) 
(list 2560.518 871.5511) 
(list 2560.5036 871.5614) 
(list 2560.4868 871.5717) 
(list 2560.4681 871.5819) 
(list 2560.4481 871.5922) 
(list 2560.4274 871.6025) 
(list 2560.4066 871.6128) 
(list 2560.3863 871.6231) 
(list 2560.3672 871.6333) 
(list 2560.3499 871.6436) 
(list 2560.3348 871.6539) 
(list 2560.3226 871.6642) 
(list 2560.3134 871.6744) 
(list 2560.3077 871.6847) 
(list 2560.3056 871.695) 
(list 2560.3073 871.7053) 
(list 2560.3126 871.7156) 
(list 2560.3214 871.7258) 
(list 2560.3335 871.7361) 
(list 2560.3485 871.7464) 
(list 2560.366 871.7567) 
(list 2560.3855 871.7669) 
(list 2560.4063 871.7772) 
(list 2560.4278 871.7875) 
(list 2560.4495 871.7978) 
(list 2560.4705 871.8081) 
(list 2560.4904 871.8183) 
(list 2560.5084 871.8286) 
(list 2560.5241 871.8389) 
(list 2560.5369 871.8492) 
(list 2560.5464 871.8594) 
(list 2560.5523 871.8697) 
(list 2560.5545 871.88) 
(list 2560.5545 871.88)))
(apply 'command (append '("pline") coords '("c")))
(setq tap8 (ssadd (entlast) tap8))
(command "_mirror" (entlast) "" "2560,900" "2560,901" "No")
(setq tap8 (ssadd (entlast) tap8))
(setq coords (list 
(list 2561.129 871.51) 
(list 2560.5545 871.51) 
(list 2560.5545 871.5203) 
(list 2560.5545 871.5306) 
(list 2560.5545 871.5408) 
(list 2560.5545 871.5511) 
(list 2560.5545 871.5614) 
(list 2560.5545 871.5717) 
(list 2560.5545 871.5819) 
(list 2560.5545 871.5922) 
(list 2560.5545 871.6025) 
(list 2560.5545 871.6128) 
(list 2560.5545 871.6231) 
(list 2560.5545 871.6333) 
(list 2560.5545 871.6436) 
(list 2560.5545 871.6539) 
(list 2560.5545 871.6642) 
(list 2560.5545 871.6744) 
(list 2560.5545 871.6847) 
(list 2560.5545 871.695) 
(list 2560.5545 871.7053) 
(list 2560.5545 871.7156) 
(list 2560.5545 871.7258) 
(list 2560.5545 871.7361) 
(list 2560.5545 871.7464) 
(list 2560.5545 871.7567) 
(list 2560.5545 871.7669) 
(list 2560.5545 871.7772) 
(list 2560.5545 871.7875) 
(list 2560.5545 871.7978) 
(list 2560.5545 871.8081) 
(list 2560.5545 871.8183) 
(list 2560.5545 871.8286) 
(list 2560.5545 871.8389) 
(list 2560.5545 871.8492) 
(list 2560.5545 871.8594) 
(list 2560.5545 871.8697) 
(list 2560.5545 871.88) 
(list 2561.129 871.88)))
(apply 'command (append '("pline") coords '("c")))
(setq tap8 (ssadd (entlast) tap8))
(command "_mirror" (entlast) "" "2560,900" "2560,901" "No")
(setq tap8 (ssadd (entlast) tap8))
(setq coords (list 
(list 2560 871.88) 
(list 2560.135 871.88) 
(list 2560.135 871.8903) 
(list 2560.135 871.9006) 
(list 2560.135 871.9108) 
(list 2560.135 871.9211) 
(list 2560.135 871.9314) 
(list 2560.135 871.9417) 
(list 2560.135 871.9519) 
(list 2560.135 871.9622) 
(list 2560.135 871.9725) 
(list 2560.135 871.9828) 
(list 2560.135 871.9931) 
(list 2560.135 872.0033) 
(list 2560.135 872.0136) 
(list 2560.135 872.0239) 
(list 2560.135 872.0342) 
(list 2560.135 872.0444) 
(list 2560.135 872.0547) 
(list 2560.135 872.065) 
(list 2560.135 872.0753) 
(list 2560.135 872.0856) 
(list 2560.135 872.0958) 
(list 2560.135 872.1061) 
(list 2560.135 872.1164) 
(list 2560.135 872.1267) 
(list 2560.135 872.1369) 
(list 2560.135 872.1472) 
(list 2560.135 872.1575) 
(list 2560.135 872.1678) 
(list 2560.135 872.1781) 
(list 2560.135 872.1883) 
(list 2560.135 872.1986) 
(list 2560.135 872.2089) 
(list 2560.135 872.2192) 
(list 2560.135 872.2294) 
(list 2560.135 872.2397) 
(list 2560.135 872.25) 
(list 2560 872.25)))
(apply 'command (append '("pline") coords '("c")))
(setq tap8 (ssadd (entlast) tap8))
(command "_mirror" (entlast) "" "2560,900" "2560,901" "No")
(setq tap8 (ssadd (entlast) tap8))
(setq coords (list 
(list 2560.5645 871.88) 
(list 2560.5545 871.88) 
(list 2560.5529 871.8903) 
(list 2560.5474 871.9006) 
(list 2560.5383 871.9108) 
(list 2560.5258 871.9211) 
(list 2560.5103 871.9314) 
(list 2560.4922 871.9417) 
(list 2560.4721 871.9519) 
(list 2560.4506 871.9622) 
(list 2560.4283 871.9725) 
(list 2560.4059 871.9828) 
(list 2560.3842 871.9931) 
(list 2560.3636 872.0033) 
(list 2560.345 872.0136) 
(list 2560.3289 872.0239) 
(list 2560.3157 872.0342) 
(list 2560.3059 872.0444) 
(list 2560.2998 872.0547) 
(list 2560.2975 872.065) 
(list 2560.2993 872.0753) 
(list 2560.305 872.0856) 
(list 2560.3145 872.0958) 
(list 2560.3275 872.1061) 
(list 2560.3437 872.1164) 
(list 2560.3624 872.1267) 
(list 2560.3833 872.1369) 
(list 2560.4056 872.1472) 
(list 2560.4288 872.1575) 
(list 2560.452 872.1678) 
(list 2560.4746 872.1781) 
(list 2560.4958 872.1883) 
(list 2560.5152 872.1986) 
(list 2560.5319 872.2089) 
(list 2560.5456 872.2192) 
(list 2560.5558 872.2294) 
(list 2560.5622 872.2397) 
(list 2560.5645 872.25) 
(list 2560.5645 872.25)))
(apply 'command (append '("pline") coords '("c")))
(setq tap8 (ssadd (entlast) tap8))
(command "_mirror" (entlast) "" "2560,900" "2560,901" "No")
(setq tap8 (ssadd (entlast) tap8))
(setq coords (list 
(list 2561.129 871.88) 
(list 2560.5645 871.88) 
(list 2560.5645 871.8903) 
(list 2560.5645 871.9006) 
(list 2560.5645 871.9108) 
(list 2560.5645 871.9211) 
(list 2560.5645 871.9314) 
(list 2560.5645 871.9417) 
(list 2560.5645 871.9519) 
(list 2560.5645 871.9622) 
(list 2560.5645 871.9725) 
(list 2560.5645 871.9828) 
(list 2560.5645 871.9931) 
(list 2560.5645 872.0033) 
(list 2560.5645 872.0136) 
(list 2560.5645 872.0239) 
(list 2560.5645 872.0342) 
(list 2560.5645 872.0444) 
(list 2560.5645 872.0547) 
(list 2560.5645 872.065) 
(list 2560.5645 872.0753) 
(list 2560.5645 872.0856) 
(list 2560.5645 872.0958) 
(list 2560.5645 872.1061) 
(list 2560.5645 872.1164) 
(list 2560.5645 872.1267) 
(list 2560.5645 872.1369) 
(list 2560.5645 872.1472) 
(list 2560.5645 872.1575) 
(list 2560.5645 872.1678) 
(list 2560.5645 872.1781) 
(list 2560.5645 872.1883) 
(list 2560.5645 872.1986) 
(list 2560.5645 872.2089) 
(list 2560.5645 872.2192) 
(list 2560.5645 872.2294) 
(list 2560.5645 872.2397) 
(list 2560.5645 872.25) 
(list 2561.129 872.25)))
(apply 'command (append '("pline") coords '("c")))
(setq tap8 (ssadd (entlast) tap8))
(command "_mirror" (entlast) "" "2560,900" "2560,901" "No")
(setq tap8 (ssadd (entlast) tap8))
(command "_block" "blktap8" "2560,900" tap8 "")
(command "_insert" "blktap8" "2560,900" "1" "1" "0")
(command "_insert" "blktap8" "2560,900" "1" "1" "180")
(setq uc8 nil)
(setq uc8 (ssadd))
(setq coords (list 
(list 0 -0.185) 
(list 0.135 -0.185) 
(list 0.135 -0.17472) 
(list 0.135 -0.16444) 
(list 0.135 -0.15417) 
(list 0.135 -0.14389) 
(list 0.135 -0.13361) 
(list 0.135 -0.12333) 
(list 0.135 -0.11306) 
(list 0.135 -0.10278) 
(list 0.135 -0.0925) 
(list 0.135 -0.082222) 
(list 0.135 -0.071944) 
(list 0.135 -0.061667) 
(list 0.135 -0.051389) 
(list 0.135 -0.041111) 
(list 0.135 -0.030833) 
(list 0.135 -0.020556) 
(list 0.135 -0.010278) 
(list 0.135 0) 
(list 0.135 0.010278) 
(list 0.135 0.020556) 
(list 0.135 0.030833) 
(list 0.135 0.041111) 
(list 0.135 0.051389) 
(list 0.135 0.061667) 
(list 0.135 0.071944) 
(list 0.135 0.082222) 
(list 0.135 0.0925) 
(list 0.135 0.10278) 
(list 0.135 0.11306) 
(list 0.135 0.12333) 
(list 0.135 0.13361) 
(list 0.135 0.14389) 
(list 0.135 0.15417) 
(list 0.135 0.16444) 
(list 0.135 0.17472) 
(list 0.135 0.185) 
(list 0 0.185)))
(apply 'command (append '("pline") coords '("c")))
(setq uc8 (ssadd (entlast) uc8))
(setq coords (list 
(list 1.129 -0.185) 
(list 0.5645 -0.185) 
(list 0.56244 -0.17472) 
(list 0.55633 -0.16444) 
(list 0.54635 -0.15417) 
(list 0.5328 -0.14389) 
(list 0.5161 -0.13361) 
(list 0.49675 -0.12333) 
(list 0.47534 -0.11306) 
(list 0.45253 -0.10278) 
(list 0.429 -0.0925) 
(list 0.40547 -0.082222) 
(list 0.38266 -0.071944) 
(list 0.36125 -0.061667) 
(list 0.3419 -0.051389) 
(list 0.3252 -0.041111) 
(list 0.31165 -0.030833) 
(list 0.30167 -0.020556) 
(list 0.29556 -0.010278) 
(list 0.2935 0) 
(list 0.29556 0.010278) 
(list 0.30167 0.020556) 
(list 0.31165 0.030833) 
(list 0.3252 0.041111) 
(list 0.3419 0.051389) 
(list 0.36125 0.061667) 
(list 0.38266 0.071944) 
(list 0.40547 0.082222) 
(list 0.429 0.0925) 
(list 0.45253 0.10278) 
(list 0.47534 0.11306) 
(list 0.49675 0.12333) 
(list 0.5161 0.13361) 
(list 0.5328 0.14389) 
(list 0.54635 0.15417) 
(list 0.55633 0.16444) 
(list 0.56244 0.17472) 
(list 0.5645 0.185) 
(list 1.129 0.185)))
(apply 'command (append '("pline") coords '("c")))
(setq uc8 (ssadd (entlast) uc8))
(command "_block" "blkuc8" "0,0.185" uc8 "")
(command "_insert" "blkuc8" "2560,872.62" "1" "1" "0")
(command "_insert" "blkuc8" "2560,872.25" "1" "1" "180")
(command "_insert" "blkuc8" "2560,872.99" "1" "1" "0")
(command "_insert" "blkuc8" "2560,872.62" "1" "1" "180")
(command "_insert" "blkuc8" "2560,873.36" "1" "1" "0")
(command "_insert" "blkuc8" "2560,872.99" "1" "1" "180")
(command "_insert" "blkuc8" "2560,873.73" "1" "1" "0")
(command "_insert" "blkuc8" "2560,873.36" "1" "1" "180")
(command "_insert" "blkuc8" "2560,874.1" "1" "1" "0")
(command "_insert" "blkuc8" "2560,873.73" "1" "1" "180")
(command "_insert" "blkuc8" "2560,874.47" "1" "1" "0")
(command "_insert" "blkuc8" "2560,874.1" "1" "1" "180")
(command "_insert" "blkuc8" "2560,874.84" "1" "1" "0")
(command "_insert" "blkuc8" "2560,874.47" "1" "1" "180")
(command "_insert" "blkuc8" "2560,875.21" "1" "1" "0")
(command "_insert" "blkuc8" "2560,874.84" "1" "1" "180")
(command "_insert" "blkuc8" "2560,875.58" "1" "1" "0")
(command "_insert" "blkuc8" "2560,875.21" "1" "1" "180")
(command "_insert" "blkuc8" "2560,875.95" "1" "1" "0")
(command "_insert" "blkuc8" "2560,875.58" "1" "1" "180")
(command "_insert" "blkuc8" "2560,876.32" "1" "1" "0")
(command "_insert" "blkuc8" "2560,875.95" "1" "1" "180")
(command "_insert" "blkuc8" "2560,876.69" "1" "1" "0")
(command "_insert" "blkuc8" "2560,876.32" "1" "1" "180")
(command "_insert" "blkuc8" "2560,877.06" "1" "1" "0")
(command "_insert" "blkuc8" "2560,876.69" "1" "1" "180")
(command "_insert" "blkuc8" "2560,877.43" "1" "1" "0")
(command "_insert" "blkuc8" "2560,877.06" "1" "1" "180")
(command "_insert" "blkuc8" "2560,877.8" "1" "1" "0")
(command "_insert" "blkuc8" "2560,877.43" "1" "1" "180")
(command "_insert" "blkuc8" "2560,878.17" "1" "1" "0")
(command "_insert" "blkuc8" "2560,877.8" "1" "1" "180")
(command "_insert" "blkuc8" "2560,878.54" "1" "1" "0")
(command "_insert" "blkuc8" "2560,878.17" "1" "1" "180")
(command "_insert" "blkuc8" "2560,878.91" "1" "1" "0")
(command "_insert" "blkuc8" "2560,878.54" "1" "1" "180")
(command "_insert" "blkuc8" "2560,879.28" "1" "1" "0")
(command "_insert" "blkuc8" "2560,878.91" "1" "1" "180")
(command "_insert" "blkuc8" "2560,879.65" "1" "1" "0")
(command "_insert" "blkuc8" "2560,879.28" "1" "1" "180")
(command "_insert" "blkuc8" "2560,880.02" "1" "1" "0")
(command "_insert" "blkuc8" "2560,879.65" "1" "1" "180")
(command "_insert" "blkuc8" "2560,880.39" "1" "1" "0")
(command "_insert" "blkuc8" "2560,880.02" "1" "1" "180")
(command "_insert" "blkuc8" "2560,880.76" "1" "1" "0")
(command "_insert" "blkuc8" "2560,880.39" "1" "1" "180")
(command "_insert" "blkuc8" "2560,881.13" "1" "1" "0")
(command "_insert" "blkuc8" "2560,880.76" "1" "1" "180")
(command "_insert" "blkuc8" "2560,881.5" "1" "1" "0")
(command "_insert" "blkuc8" "2560,881.13" "1" "1" "180")
(command "_insert" "blkuc8" "2560,881.87" "1" "1" "0")
(command "_insert" "blkuc8" "2560,881.5" "1" "1" "180")
(command "_insert" "blkuc8" "2560,882.24" "1" "1" "0")
(command "_insert" "blkuc8" "2560,881.87" "1" "1" "180")
(command "_insert" "blkuc8" "2560,882.61" "1" "1" "0")
(command "_insert" "blkuc8" "2560,882.24" "1" "1" "180")
(command "_insert" "blkuc8" "2560,882.98" "1" "1" "0")
(command "_insert" "blkuc8" "2560,882.61" "1" "1" "180")
(command "_insert" "blkuc8" "2560,883.35" "1" "1" "0")
(command "_insert" "blkuc8" "2560,882.98" "1" "1" "180")
(command "_insert" "blkuc8" "2560,883.72" "1" "1" "0")
(command "_insert" "blkuc8" "2560,883.35" "1" "1" "180")
(command "_insert" "blkuc8" "2560,884.09" "1" "1" "0")
(command "_insert" "blkuc8" "2560,883.72" "1" "1" "180")
(command "_insert" "blkuc8" "2560,884.46" "1" "1" "0")
(command "_insert" "blkuc8" "2560,884.09" "1" "1" "180")
(command "_insert" "blkuc8" "2560,884.83" "1" "1" "0")
(command "_insert" "blkuc8" "2560,884.46" "1" "1" "180")
(command "_insert" "blkuc8" "2560,885.2" "1" "1" "0")
(command "_insert" "blkuc8" "2560,884.83" "1" "1" "180")
(command "_insert" "blkuc8" "2560,885.57" "1" "1" "0")
(command "_insert" "blkuc8" "2560,885.2" "1" "1" "180")
(command "_insert" "blkuc8" "2560,885.94" "1" "1" "0")
(command "_insert" "blkuc8" "2560,885.57" "1" "1" "180")
(command "_insert" "blkuc8" "2560,886.31" "1" "1" "0")
(command "_insert" "blkuc8" "2560,885.94" "1" "1" "180")
(command "_insert" "blkuc8" "2560,886.68" "1" "1" "0")
(command "_insert" "blkuc8" "2560,886.31" "1" "1" "180")
(command "_insert" "blkuc8" "2560,887.05" "1" "1" "0")
(command "_insert" "blkuc8" "2560,886.68" "1" "1" "180")
(command "_insert" "blkuc8" "2560,887.42" "1" "1" "0")
(command "_insert" "blkuc8" "2560,887.05" "1" "1" "180")
(command "_insert" "blkuc8" "2560,887.79" "1" "1" "0")
(command "_insert" "blkuc8" "2560,887.42" "1" "1" "180")
(command "_insert" "blkuc8" "2560,888.16" "1" "1" "0")
(command "_insert" "blkuc8" "2560,887.79" "1" "1" "180")
(command "_insert" "blkuc8" "2560,888.53" "1" "1" "0")
(command "_insert" "blkuc8" "2560,888.16" "1" "1" "180")
(command "_insert" "blkuc8" "2560,888.9" "1" "1" "0")
(command "_insert" "blkuc8" "2560,888.53" "1" "1" "180")
(command "_insert" "blkuc8" "2560,889.27" "1" "1" "0")
(command "_insert" "blkuc8" "2560,888.9" "1" "1" "180")
(command "_insert" "blkuc8" "2560,889.64" "1" "1" "0")
(command "_insert" "blkuc8" "2560,889.27" "1" "1" "180")
(command "_insert" "blkuc8" "2560,890.01" "1" "1" "0")
(command "_insert" "blkuc8" "2560,889.64" "1" "1" "180")
(command "_insert" "blkuc8" "2560,890.38" "1" "1" "0")
(command "_insert" "blkuc8" "2560,890.01" "1" "1" "180")
(command "_insert" "blkuc8" "2560,890.75" "1" "1" "0")
(command "_insert" "blkuc8" "2560,890.38" "1" "1" "180")
(command "_insert" "blkuc8" "2560,891.12" "1" "1" "0")
(command "_insert" "blkuc8" "2560,890.75" "1" "1" "180")
(command "_insert" "blkuc8" "2560,891.49" "1" "1" "0")
(command "_insert" "blkuc8" "2560,891.12" "1" "1" "180")
(command "_insert" "blkuc8" "2560,891.86" "1" "1" "0")
(command "_insert" "blkuc8" "2560,891.49" "1" "1" "180")
(command "_insert" "blkuc8" "2560,892.23" "1" "1" "0")
(command "_insert" "blkuc8" "2560,891.86" "1" "1" "180")
(command "_insert" "blkuc8" "2560,892.6" "1" "1" "0")
(command "_insert" "blkuc8" "2560,892.23" "1" "1" "180")
(command "_insert" "blkuc8" "2560,892.97" "1" "1" "0")
(command "_insert" "blkuc8" "2560,892.6" "1" "1" "180")
(command "_insert" "blkuc8" "2560,893.34" "1" "1" "0")
(command "_insert" "blkuc8" "2560,892.97" "1" "1" "180")
(command "_insert" "blkuc8" "2560,893.71" "1" "1" "0")
(command "_insert" "blkuc8" "2560,893.34" "1" "1" "180")
(command "_insert" "blkuc8" "2560,894.08" "1" "1" "0")
(command "_insert" "blkuc8" "2560,893.71" "1" "1" "180")
(command "_insert" "blkuc8" "2560,894.45" "1" "1" "0")
(command "_insert" "blkuc8" "2560,894.08" "1" "1" "180")
(command "_insert" "blkuc8" "2560,894.82" "1" "1" "0")
(command "_insert" "blkuc8" "2560,894.45" "1" "1" "180")
(command "_insert" "blkuc8" "2560,895.19" "1" "1" "0")
(command "_insert" "blkuc8" "2560,894.82" "1" "1" "180")
(command "_insert" "blkuc8" "2560,895.56" "1" "1" "0")
(command "_insert" "blkuc8" "2560,895.19" "1" "1" "180")
(command "_insert" "blkuc8" "2560,895.93" "1" "1" "0")
(command "_insert" "blkuc8" "2560,895.56" "1" "1" "180")
(command "_insert" "blkuc8" "2560,896.3" "1" "1" "0")
(command "_insert" "blkuc8" "2560,895.93" "1" "1" "180")
(command "_insert" "blkuc8" "2560,896.67" "1" "1" "0")
(command "_insert" "blkuc8" "2560,896.3" "1" "1" "180")
(command "_insert" "blkuc8" "2560,897.04" "1" "1" "0")
(command "_insert" "blkuc8" "2560,896.67" "1" "1" "180")
(command "_insert" "blkuc8" "2560,897.41" "1" "1" "0")
(command "_insert" "blkuc8" "2560,897.04" "1" "1" "180")
(command "_insert" "blkuc8" "2560,897.78" "1" "1" "0")
(command "_insert" "blkuc8" "2560,897.41" "1" "1" "180")
(command "_insert" "blkuc8" "2560,898.15" "1" "1" "0")
(command "_insert" "blkuc8" "2560,897.78" "1" "1" "180")
(command "_insert" "blkuc8" "2560,898.52" "1" "1" "0")
(command "_insert" "blkuc8" "2560,898.15" "1" "1" "180")
(command "_insert" "blkuc8" "2560,898.89" "1" "1" "0")
(command "_insert" "blkuc8" "2560,898.52" "1" "1" "180")
(command "_insert" "blkuc8" "2560,899.26" "1" "1" "0")
(command "_insert" "blkuc8" "2560,898.89" "1" "1" "180")
(command "_insert" "blkuc8" "2560,899.63" "1" "1" "0")
(command "_insert" "blkuc8" "2560,899.26" "1" "1" "180")
(command "_insert" "blkuc8" "2560,900" "1" "1" "0")
(command "_insert" "blkuc8" "2560,899.63" "1" "1" "180")
(command "_insert" "blkuc8" "2560,900.37" "1" "1" "0")
(command "_insert" "blkuc8" "2560,900" "1" "1" "180")
(command "_insert" "blkuc8" "2560,900.74" "1" "1" "0")
(command "_insert" "blkuc8" "2560,900.37" "1" "1" "180")
(command "_insert" "blkuc8" "2560,901.11" "1" "1" "0")
(command "_insert" "blkuc8" "2560,900.74" "1" "1" "180")
(command "_insert" "blkuc8" "2560,901.48" "1" "1" "0")
(command "_insert" "blkuc8" "2560,901.11" "1" "1" "180")
(command "_insert" "blkuc8" "2560,901.85" "1" "1" "0")
(command "_insert" "blkuc8" "2560,901.48" "1" "1" "180")
(command "_insert" "blkuc8" "2560,902.22" "1" "1" "0")
(command "_insert" "blkuc8" "2560,901.85" "1" "1" "180")
(command "_insert" "blkuc8" "2560,902.59" "1" "1" "0")
(command "_insert" "blkuc8" "2560,902.22" "1" "1" "180")
(command "_insert" "blkuc8" "2560,902.96" "1" "1" "0")
(command "_insert" "blkuc8" "2560,902.59" "1" "1" "180")
(command "_insert" "blkuc8" "2560,903.33" "1" "1" "0")
(command "_insert" "blkuc8" "2560,902.96" "1" "1" "180")
(command "_insert" "blkuc8" "2560,903.7" "1" "1" "0")
(command "_insert" "blkuc8" "2560,903.33" "1" "1" "180")
(command "_insert" "blkuc8" "2560,904.07" "1" "1" "0")
(command "_insert" "blkuc8" "2560,903.7" "1" "1" "180")
(command "_insert" "blkuc8" "2560,904.44" "1" "1" "0")
(command "_insert" "blkuc8" "2560,904.07" "1" "1" "180")
(command "_insert" "blkuc8" "2560,904.81" "1" "1" "0")
(command "_insert" "blkuc8" "2560,904.44" "1" "1" "180")
(command "_insert" "blkuc8" "2560,905.18" "1" "1" "0")
(command "_insert" "blkuc8" "2560,904.81" "1" "1" "180")
(command "_insert" "blkuc8" "2560,905.55" "1" "1" "0")
(command "_insert" "blkuc8" "2560,905.18" "1" "1" "180")
(command "_insert" "blkuc8" "2560,905.92" "1" "1" "0")
(command "_insert" "blkuc8" "2560,905.55" "1" "1" "180")
(command "_insert" "blkuc8" "2560,906.29" "1" "1" "0")
(command "_insert" "blkuc8" "2560,905.92" "1" "1" "180")
(command "_insert" "blkuc8" "2560,906.66" "1" "1" "0")
(command "_insert" "blkuc8" "2560,906.29" "1" "1" "180")
(command "_insert" "blkuc8" "2560,907.03" "1" "1" "0")
(command "_insert" "blkuc8" "2560,906.66" "1" "1" "180")
(command "_insert" "blkuc8" "2560,907.4" "1" "1" "0")
(command "_insert" "blkuc8" "2560,907.03" "1" "1" "180")
(command "_insert" "blkuc8" "2560,907.77" "1" "1" "0")
(command "_insert" "blkuc8" "2560,907.4" "1" "1" "180")
(command "_insert" "blkuc8" "2560,908.14" "1" "1" "0")
(command "_insert" "blkuc8" "2560,907.77" "1" "1" "180")
(command "_insert" "blkuc8" "2560,908.51" "1" "1" "0")
(command "_insert" "blkuc8" "2560,908.14" "1" "1" "180")
(command "_insert" "blkuc8" "2560,908.88" "1" "1" "0")
(command "_insert" "blkuc8" "2560,908.51" "1" "1" "180")
(command "_insert" "blkuc8" "2560,909.25" "1" "1" "0")
(command "_insert" "blkuc8" "2560,908.88" "1" "1" "180")
(command "_insert" "blkuc8" "2560,909.62" "1" "1" "0")
(command "_insert" "blkuc8" "2560,909.25" "1" "1" "180")
(command "_insert" "blkuc8" "2560,909.99" "1" "1" "0")
(command "_insert" "blkuc8" "2560,909.62" "1" "1" "180")
(command "_insert" "blkuc8" "2560,910.36" "1" "1" "0")
(command "_insert" "blkuc8" "2560,909.99" "1" "1" "180")
(command "_insert" "blkuc8" "2560,910.73" "1" "1" "0")
(command "_insert" "blkuc8" "2560,910.36" "1" "1" "180")
(command "_insert" "blkuc8" "2560,911.1" "1" "1" "0")
(command "_insert" "blkuc8" "2560,910.73" "1" "1" "180")
(command "_insert" "blkuc8" "2560,911.47" "1" "1" "0")
(command "_insert" "blkuc8" "2560,911.1" "1" "1" "180")
(command "_insert" "blkuc8" "2560,911.84" "1" "1" "0")
(command "_insert" "blkuc8" "2560,911.47" "1" "1" "180")
(command "_insert" "blkuc8" "2560,912.21" "1" "1" "0")
(command "_insert" "blkuc8" "2560,911.84" "1" "1" "180")
(command "_insert" "blkuc8" "2560,912.58" "1" "1" "0")
(command "_insert" "blkuc8" "2560,912.21" "1" "1" "180")
(command "_insert" "blkuc8" "2560,912.95" "1" "1" "0")
(command "_insert" "blkuc8" "2560,912.58" "1" "1" "180")
(command "_insert" "blkuc8" "2560,913.32" "1" "1" "0")
(command "_insert" "blkuc8" "2560,912.95" "1" "1" "180")
(command "_insert" "blkuc8" "2560,913.69" "1" "1" "0")
(command "_insert" "blkuc8" "2560,913.32" "1" "1" "180")
(command "_insert" "blkuc8" "2560,914.06" "1" "1" "0")
(command "_insert" "blkuc8" "2560,913.69" "1" "1" "180")
(command "_insert" "blkuc8" "2560,914.43" "1" "1" "0")
(command "_insert" "blkuc8" "2560,914.06" "1" "1" "180")
(command "_insert" "blkuc8" "2560,914.8" "1" "1" "0")
(command "_insert" "blkuc8" "2560,914.43" "1" "1" "180")
(command "_insert" "blkuc8" "2560,915.17" "1" "1" "0")
(command "_insert" "blkuc8" "2560,914.8" "1" "1" "180")
(command "_insert" "blkuc8" "2560,915.54" "1" "1" "0")
(command "_insert" "blkuc8" "2560,915.17" "1" "1" "180")
(command "_insert" "blkuc8" "2560,915.91" "1" "1" "0")
(command "_insert" "blkuc8" "2560,915.54" "1" "1" "180")
(command "_insert" "blkuc8" "2560,916.28" "1" "1" "0")
(command "_insert" "blkuc8" "2560,915.91" "1" "1" "180")
(command "_insert" "blkuc8" "2560,916.65" "1" "1" "0")
(command "_insert" "blkuc8" "2560,916.28" "1" "1" "180")
(command "_insert" "blkuc8" "2560,917.02" "1" "1" "0")
(command "_insert" "blkuc8" "2560,916.65" "1" "1" "180")
(command "_insert" "blkuc8" "2560,917.39" "1" "1" "0")
(command "_insert" "blkuc8" "2560,917.02" "1" "1" "180")
(command "_insert" "blkuc8" "2560,917.76" "1" "1" "0")
(command "_insert" "blkuc8" "2560,917.39" "1" "1" "180")
(command "_insert" "blkuc8" "2560,918.13" "1" "1" "0")
(command "_insert" "blkuc8" "2560,917.76" "1" "1" "180")
(command "_insert" "blkuc8" "2560,918.5" "1" "1" "0")
(command "_insert" "blkuc8" "2560,918.13" "1" "1" "180")
(command "_insert" "blkuc8" "2560,918.87" "1" "1" "0")
(command "_insert" "blkuc8" "2560,918.5" "1" "1" "180")
(command "_insert" "blkuc8" "2560,919.24" "1" "1" "0")
(command "_insert" "blkuc8" "2560,918.87" "1" "1" "180")
(command "_insert" "blkuc8" "2560,919.61" "1" "1" "0")
(command "_insert" "blkuc8" "2560,919.24" "1" "1" "180")
(command "_insert" "blkuc8" "2560,919.98" "1" "1" "0")
(command "_insert" "blkuc8" "2560,919.61" "1" "1" "180")
(command "_insert" "blkuc8" "2560,920.35" "1" "1" "0")
(command "_insert" "blkuc8" "2560,919.98" "1" "1" "180")
(command "_insert" "blkuc8" "2560,920.72" "1" "1" "0")
(command "_insert" "blkuc8" "2560,920.35" "1" "1" "180")
(command "_insert" "blkuc8" "2560,921.09" "1" "1" "0")
(command "_insert" "blkuc8" "2560,920.72" "1" "1" "180")
(command "_insert" "blkuc8" "2560,921.46" "1" "1" "0")
(command "_insert" "blkuc8" "2560,921.09" "1" "1" "180")
(command "_insert" "blkuc8" "2560,921.83" "1" "1" "0")
(command "_insert" "blkuc8" "2560,921.46" "1" "1" "180")
(command "_insert" "blkuc8" "2560,922.2" "1" "1" "0")
(command "_insert" "blkuc8" "2560,921.83" "1" "1" "180")
(command "_insert" "blkuc8" "2560,922.57" "1" "1" "0")
(command "_insert" "blkuc8" "2560,922.2" "1" "1" "180")
(command "_insert" "blkuc8" "2560,922.94" "1" "1" "0")
(command "_insert" "blkuc8" "2560,922.57" "1" "1" "180")
(command "_insert" "blkuc8" "2560,923.31" "1" "1" "0")
(command "_insert" "blkuc8" "2560,922.94" "1" "1" "180")
(command "_insert" "blkuc8" "2560,923.68" "1" "1" "0")
(command "_insert" "blkuc8" "2560,923.31" "1" "1" "180")
(command "_insert" "blkuc8" "2560,924.05" "1" "1" "0")
(command "_insert" "blkuc8" "2560,923.68" "1" "1" "180")
(command "_insert" "blkuc8" "2560,924.42" "1" "1" "0")
(command "_insert" "blkuc8" "2560,924.05" "1" "1" "180")
(command "_insert" "blkuc8" "2560,924.79" "1" "1" "0")
(command "_insert" "blkuc8" "2560,924.42" "1" "1" "180")
(command "_insert" "blkuc8" "2560,925.16" "1" "1" "0")
(command "_insert" "blkuc8" "2560,924.79" "1" "1" "180")
(command "_insert" "blkuc8" "2560,925.53" "1" "1" "0")
(command "_insert" "blkuc8" "2560,925.16" "1" "1" "180")
(command "_insert" "blkuc8" "2560,925.9" "1" "1" "0")
(command "_insert" "blkuc8" "2560,925.53" "1" "1" "180")
(command "_insert" "blkuc8" "2560,926.27" "1" "1" "0")
(command "_insert" "blkuc8" "2560,925.9" "1" "1" "180")
(command "_insert" "blkuc8" "2560,926.64" "1" "1" "0")
(command "_insert" "blkuc8" "2560,926.27" "1" "1" "180")
(command "_insert" "blkuc8" "2560,927.01" "1" "1" "0")
(command "_insert" "blkuc8" "2560,926.64" "1" "1" "180")
(command "_insert" "blkuc8" "2560,927.38" "1" "1" "0")
(command "_insert" "blkuc8" "2560,927.01" "1" "1" "180")
(command "_insert" "blkuc8" "2560,927.75" "1" "1" "0")
(command "_insert" "blkuc8" "2560,927.38" "1" "1" "180")
(command "_layer" "set" "phccover" "")
(command "_rectangle" "2558.871,933.3" "2561.129,866.7")
(command "_layer" "set" "nitride" "")
(setq phc8 currobj)
(command "_layer" "set" "cover" "")
(command "_rectangle" "2558.871,836.7" "2561.129,963.3")
(command "_layer" "set" "nitride" "")
(command "_layer" "set" "text" "")
(command "_circle" "2557.921,846.7" "0.075")
(command "_circle" "2557.546,846.7" "0.15")
(command "_circle" "2557.171,846.7" "0.075")
(command "_circle" "2556.796,846.7" "0.15")
(command "_circle" "2557.921,848.7" "0.075")
(command "_circle" "2557.546,848.7" "0.075")
(command "_circle" "2557.171,848.7" "0.15")
(command "_circle" "2556.796,848.7" "0.15")
(command "_circle" "2557.921,850.7" "0.075")
(command "_circle" "2557.546,850.7" "0.15")
(command "_circle" "2557.171,850.7" "0.15")
(command "_circle" "2556.796,850.7" "0.15")
(command "_circle" "2557.921,852.7" "0.075")
(command "_circle" "2557.546,852.7" "0.075")
(command "_circle" "2557.171,852.7" "0.075")
(command "_circle" "2556.796,852.7" "0.075")
(command "_circle" "2556.421,852.7" "0.15")
(command "_circle" "2557.921,854.7" "0.075")
(command "_circle" "2557.546,854.7" "0.15")
(command "_circle" "2557.171,854.7" "0.075")
(command "_circle" "2556.796,854.7" "0.075")
(command "_circle" "2556.421,854.7" "0.15")
(command "_circle" "2557.921,856.7" "0.075")
(command "_circle" "2557.546,856.7" "0.075")
(command "_circle" "2557.171,856.7" "0.15")
(command "_circle" "2556.796,856.7" "0.075")
(command "_circle" "2556.421,856.7" "0.15")
(command "_circle" "2557.921,858.7" "0.075")
(command "_circle" "2557.546,858.7" "0.15")
(command "_circle" "2557.171,858.7" "0.15")
(command "_circle" "2556.796,858.7" "0.075")
(command "_circle" "2556.421,858.7" "0.15")
(command "_circle" "2557.921,860.7" "0.075")
(command "_circle" "2557.546,860.7" "0.075")
(command "_circle" "2557.171,860.7" "0.075")
(command "_circle" "2556.796,860.7" "0.15")
(command "_circle" "2556.421,860.7" "0.15")
(command "_circle" "2557.921,862.7" "0.075")
(command "_circle" "2557.546,862.7" "0.15")
(command "_circle" "2557.171,862.7" "0.075")
(command "_circle" "2556.796,862.7" "0.15")
(command "_circle" "2556.421,862.7" "0.15")
(command "_circle" "2557.921,864.7" "0.075")
(command "_circle" "2557.546,864.7" "0.075")
(command "_circle" "2557.171,864.7" "0.15")
(command "_circle" "2556.796,864.7" "0.15")
(command "_circle" "2556.421,864.7" "0.15")
(command "_circle" "2557.921,866.7" "0.075")
(command "_circle" "2557.546,866.7" "0.15")
(command "_circle" "2557.171,866.7" "0.15")
(command "_circle" "2556.796,866.7" "0.15")
(command "_circle" "2556.421,866.7" "0.15")
(command "_circle" "2557.921,868.7" "0.075")
(command "_circle" "2557.546,868.7" "0.075")
(command "_circle" "2557.171,868.7" "0.075")
(command "_circle" "2556.796,868.7" "0.075")
(command "_circle" "2556.421,868.7" "0.075")
(command "_circle" "2556.046,868.7" "0.15")
(command "_circle" "2557.921,870.7" "0.075")
(command "_circle" "2557.546,870.7" "0.15")
(command "_circle" "2557.171,870.7" "0.075")
(command "_circle" "2556.796,870.7" "0.075")
(command "_circle" "2556.421,870.7" "0.075")
(command "_circle" "2556.046,870.7" "0.15")
(command "_circle" "2557.921,872.7" "0.075")
(command "_circle" "2557.546,872.7" "0.075")
(command "_circle" "2557.171,872.7" "0.15")
(command "_circle" "2556.796,872.7" "0.075")
(command "_circle" "2556.421,872.7" "0.075")
(command "_circle" "2556.046,872.7" "0.15")
(command "_circle" "2557.921,874.7" "0.075")
(command "_circle" "2557.546,874.7" "0.15")
(command "_circle" "2557.171,874.7" "0.15")
(command "_circle" "2556.796,874.7" "0.075")
(command "_circle" "2556.421,874.7" "0.075")
(command "_circle" "2556.046,874.7" "0.15")
(command "_circle" "2557.921,876.7" "0.075")
(command "_circle" "2557.546,876.7" "0.075")
(command "_circle" "2557.171,876.7" "0.075")
(command "_circle" "2556.796,876.7" "0.15")
(command "_circle" "2556.421,876.7" "0.075")
(command "_circle" "2556.046,876.7" "0.15")
(command "_circle" "2557.921,878.7" "0.075")
(command "_circle" "2557.546,878.7" "0.15")
(command "_circle" "2557.171,878.7" "0.075")
(command "_circle" "2556.796,878.7" "0.15")
(command "_circle" "2556.421,878.7" "0.075")
(command "_circle" "2556.046,878.7" "0.15")
(command "_circle" "2557.921,880.7" "0.075")
(command "_circle" "2557.546,880.7" "0.075")
(command "_circle" "2557.171,880.7" "0.15")
(command "_circle" "2556.796,880.7" "0.15")
(command "_circle" "2556.421,880.7" "0.075")
(command "_circle" "2556.046,880.7" "0.15")
(command "_circle" "2557.921,882.7" "0.075")
(command "_circle" "2557.546,882.7" "0.15")
(command "_circle" "2557.171,882.7" "0.15")
(command "_circle" "2556.796,882.7" "0.15")
(command "_circle" "2556.421,882.7" "0.075")
(command "_circle" "2556.046,882.7" "0.15")
(command "_circle" "2557.921,884.7" "0.075")
(command "_circle" "2557.546,884.7" "0.075")
(command "_circle" "2557.171,884.7" "0.075")
(command "_circle" "2556.796,884.7" "0.075")
(command "_circle" "2556.421,884.7" "0.15")
(command "_circle" "2556.046,884.7" "0.15")
(command "_circle" "2557.921,886.7" "0.075")
(command "_circle" "2557.546,886.7" "0.15")
(command "_circle" "2557.171,886.7" "0.075")
(command "_circle" "2556.796,886.7" "0.075")
(command "_circle" "2556.421,886.7" "0.15")
(command "_circle" "2556.046,886.7" "0.15")
(command "_circle" "2557.921,888.7" "0.075")
(command "_circle" "2557.546,888.7" "0.075")
(command "_circle" "2557.171,888.7" "0.15")
(command "_circle" "2556.796,888.7" "0.075")
(command "_circle" "2556.421,888.7" "0.15")
(command "_circle" "2556.046,888.7" "0.15")
(command "_circle" "2557.921,890.7" "0.075")
(command "_circle" "2557.546,890.7" "0.15")
(command "_circle" "2557.171,890.7" "0.15")
(command "_circle" "2556.796,890.7" "0.075")
(command "_circle" "2556.421,890.7" "0.15")
(command "_circle" "2556.046,890.7" "0.15")
(command "_circle" "2557.921,892.7" "0.075")
(command "_circle" "2557.546,892.7" "0.075")
(command "_circle" "2557.171,892.7" "0.075")
(command "_circle" "2556.796,892.7" "0.15")
(command "_circle" "2556.421,892.7" "0.15")
(command "_circle" "2556.046,892.7" "0.15")
(command "_circle" "2557.921,894.7" "0.075")
(command "_circle" "2557.546,894.7" "0.15")
(command "_circle" "2557.171,894.7" "0.075")
(command "_circle" "2556.796,894.7" "0.15")
(command "_circle" "2556.421,894.7" "0.15")
(command "_circle" "2556.046,894.7" "0.15")
(command "_circle" "2557.921,896.7" "0.075")
(command "_circle" "2557.546,896.7" "0.075")
(command "_circle" "2557.171,896.7" "0.15")
(command "_circle" "2556.796,896.7" "0.15")
(command "_circle" "2556.421,896.7" "0.15")
(command "_circle" "2556.046,896.7" "0.15")
(command "_circle" "2557.921,898.7" "0.075")
(command "_circle" "2557.546,898.7" "0.15")
(command "_circle" "2557.171,898.7" "0.15")
(command "_circle" "2556.796,898.7" "0.15")
(command "_circle" "2556.421,898.7" "0.15")
(command "_circle" "2556.046,898.7" "0.15")
(command "_circle" "2557.921,900.7" "0.075")
(command "_circle" "2557.546,900.7" "0.075")
(command "_circle" "2557.171,900.7" "0.075")
(command "_circle" "2556.796,900.7" "0.075")
(command "_circle" "2556.421,900.7" "0.075")
(command "_circle" "2556.046,900.7" "0.075")
(command "_circle" "2555.671,900.7" "0.15")
(command "_circle" "2557.921,902.7" "0.075")
(command "_circle" "2557.546,902.7" "0.15")
(command "_circle" "2557.171,902.7" "0.075")
(command "_circle" "2556.796,902.7" "0.075")
(command "_circle" "2556.421,902.7" "0.075")
(command "_circle" "2556.046,902.7" "0.075")
(command "_circle" "2555.671,902.7" "0.15")
(command "_circle" "2557.921,904.7" "0.075")
(command "_circle" "2557.546,904.7" "0.075")
(command "_circle" "2557.171,904.7" "0.15")
(command "_circle" "2556.796,904.7" "0.075")
(command "_circle" "2556.421,904.7" "0.075")
(command "_circle" "2556.046,904.7" "0.075")
(command "_circle" "2555.671,904.7" "0.15")
(command "_circle" "2557.921,906.7" "0.075")
(command "_circle" "2557.546,906.7" "0.15")
(command "_circle" "2557.171,906.7" "0.15")
(command "_circle" "2556.796,906.7" "0.075")
(command "_circle" "2556.421,906.7" "0.075")
(command "_circle" "2556.046,906.7" "0.075")
(command "_circle" "2555.671,906.7" "0.15")
(command "_circle" "2557.921,908.7" "0.075")
(command "_circle" "2557.546,908.7" "0.075")
(command "_circle" "2557.171,908.7" "0.075")
(command "_circle" "2556.796,908.7" "0.15")
(command "_circle" "2556.421,908.7" "0.075")
(command "_circle" "2556.046,908.7" "0.075")
(command "_circle" "2555.671,908.7" "0.15")
(command "_circle" "2557.921,910.7" "0.075")
(command "_circle" "2557.546,910.7" "0.15")
(command "_circle" "2557.171,910.7" "0.075")
(command "_circle" "2556.796,910.7" "0.15")
(command "_circle" "2556.421,910.7" "0.075")
(command "_circle" "2556.046,910.7" "0.075")
(command "_circle" "2555.671,910.7" "0.15")
(command "_circle" "2557.921,912.7" "0.075")
(command "_circle" "2557.546,912.7" "0.075")
(command "_circle" "2557.171,912.7" "0.15")
(command "_circle" "2556.796,912.7" "0.15")
(command "_circle" "2556.421,912.7" "0.075")
(command "_circle" "2556.046,912.7" "0.075")
(command "_circle" "2555.671,912.7" "0.15")
(command "_circle" "2557.921,914.7" "0.075")
(command "_circle" "2557.546,914.7" "0.15")
(command "_circle" "2557.171,914.7" "0.15")
(command "_circle" "2556.796,914.7" "0.15")
(command "_circle" "2556.421,914.7" "0.075")
(command "_circle" "2556.046,914.7" "0.075")
(command "_circle" "2555.671,914.7" "0.15")
(command "_circle" "2557.921,916.7" "0.075")
(command "_circle" "2557.546,916.7" "0.075")
(command "_circle" "2557.171,916.7" "0.075")
(command "_circle" "2556.796,916.7" "0.075")
(command "_circle" "2556.421,916.7" "0.15")
(command "_circle" "2556.046,916.7" "0.075")
(command "_circle" "2555.671,916.7" "0.15")
(command "_circle" "2557.921,918.7" "0.075")
(command "_circle" "2557.546,918.7" "0.15")
(command "_circle" "2557.171,918.7" "0.075")
(command "_circle" "2556.796,918.7" "0.075")
(command "_circle" "2556.421,918.7" "0.15")
(command "_circle" "2556.046,918.7" "0.075")
(command "_circle" "2555.671,918.7" "0.15")
(command "_circle" "2557.921,920.7" "0.075")
(command "_circle" "2557.546,920.7" "0.075")
(command "_circle" "2557.171,920.7" "0.15")
(command "_circle" "2556.796,920.7" "0.075")
(command "_circle" "2556.421,920.7" "0.15")
(command "_circle" "2556.046,920.7" "0.075")
(command "_circle" "2555.671,920.7" "0.15")
(command "_circle" "2557.921,922.7" "0.075")
(command "_circle" "2557.546,922.7" "0.15")
(command "_circle" "2557.171,922.7" "0.15")
(command "_circle" "2556.796,922.7" "0.075")
(command "_circle" "2556.421,922.7" "0.15")
(command "_circle" "2556.046,922.7" "0.075")
(command "_circle" "2555.671,922.7" "0.15")
(command "_circle" "2557.921,924.7" "0.075")
(command "_circle" "2557.546,924.7" "0.075")
(command "_circle" "2557.171,924.7" "0.075")
(command "_circle" "2556.796,924.7" "0.15")
(command "_circle" "2556.421,924.7" "0.15")
(command "_circle" "2556.046,924.7" "0.075")
(command "_circle" "2555.671,924.7" "0.15")
(command "_circle" "2557.921,926.7" "0.075")
(command "_circle" "2557.546,926.7" "0.15")
(command "_circle" "2557.171,926.7" "0.075")
(command "_circle" "2556.796,926.7" "0.15")
(command "_circle" "2556.421,926.7" "0.15")
(command "_circle" "2556.046,926.7" "0.075")
(command "_circle" "2555.671,926.7" "0.15")
(command "_circle" "2557.921,928.7" "0.075")
(command "_circle" "2557.546,928.7" "0.075")
(command "_circle" "2557.171,928.7" "0.15")
(command "_circle" "2556.796,928.7" "0.15")
(command "_circle" "2556.421,928.7" "0.15")
(command "_circle" "2556.046,928.7" "0.075")
(command "_circle" "2555.671,928.7" "0.15")
(command "_circle" "2557.921,930.7" "0.075")
(command "_circle" "2557.546,930.7" "0.15")
(command "_circle" "2557.171,930.7" "0.15")
(command "_circle" "2556.796,930.7" "0.15")
(command "_circle" "2556.421,930.7" "0.15")
(command "_circle" "2556.046,930.7" "0.075")
(command "_circle" "2555.671,930.7" "0.15")
(command "_circle" "2557.921,932.7" "0.075")
(command "_circle" "2557.546,932.7" "0.075")
(command "_circle" "2557.171,932.7" "0.075")
(command "_circle" "2556.796,932.7" "0.075")
(command "_circle" "2556.421,932.7" "0.075")
(command "_circle" "2556.046,932.7" "0.15")
(command "_circle" "2555.671,932.7" "0.15")
(command "_circle" "2557.921,934.7" "0.075")
(command "_circle" "2557.546,934.7" "0.15")
(command "_circle" "2557.171,934.7" "0.075")
(command "_circle" "2556.796,934.7" "0.075")
(command "_circle" "2556.421,934.7" "0.075")
(command "_circle" "2556.046,934.7" "0.15")
(command "_circle" "2555.671,934.7" "0.15")
(command "_circle" "2557.921,936.7" "0.075")
(command "_circle" "2557.546,936.7" "0.075")
(command "_circle" "2557.171,936.7" "0.15")
(command "_circle" "2556.796,936.7" "0.075")
(command "_circle" "2556.421,936.7" "0.075")
(command "_circle" "2556.046,936.7" "0.15")
(command "_circle" "2555.671,936.7" "0.15")
(command "_circle" "2557.921,938.7" "0.075")
(command "_circle" "2557.546,938.7" "0.15")
(command "_circle" "2557.171,938.7" "0.15")
(command "_circle" "2556.796,938.7" "0.075")
(command "_circle" "2556.421,938.7" "0.075")
(command "_circle" "2556.046,938.7" "0.15")
(command "_circle" "2555.671,938.7" "0.15")
(command "_circle" "2557.921,940.7" "0.075")
(command "_circle" "2557.546,940.7" "0.075")
(command "_circle" "2557.171,940.7" "0.075")
(command "_circle" "2556.796,940.7" "0.15")
(command "_circle" "2556.421,940.7" "0.075")
(command "_circle" "2556.046,940.7" "0.15")
(command "_circle" "2555.671,940.7" "0.15")
(command "_circle" "2557.921,942.7" "0.075")
(command "_circle" "2557.546,942.7" "0.15")
(command "_circle" "2557.171,942.7" "0.075")
(command "_circle" "2556.796,942.7" "0.15")
(command "_circle" "2556.421,942.7" "0.075")
(command "_circle" "2556.046,942.7" "0.15")
(command "_circle" "2555.671,942.7" "0.15")
(command "_circle" "2557.921,944.7" "0.075")
(command "_circle" "2557.546,944.7" "0.075")
(command "_circle" "2557.171,944.7" "0.15")
(command "_circle" "2556.796,944.7" "0.15")
(command "_circle" "2556.421,944.7" "0.075")
(command "_circle" "2556.046,944.7" "0.15")
(command "_circle" "2555.671,944.7" "0.15")
(command "_circle" "2557.921,946.7" "0.075")
(command "_circle" "2557.546,946.7" "0.15")
(command "_circle" "2557.171,946.7" "0.15")
(command "_circle" "2556.796,946.7" "0.15")
(command "_circle" "2556.421,946.7" "0.075")
(command "_circle" "2556.046,946.7" "0.15")
(command "_circle" "2555.671,946.7" "0.15")
(command "_circle" "2557.921,948.7" "0.075")
(command "_circle" "2557.546,948.7" "0.075")
(command "_circle" "2557.171,948.7" "0.075")
(command "_circle" "2556.796,948.7" "0.075")
(command "_circle" "2556.421,948.7" "0.15")
(command "_circle" "2556.046,948.7" "0.15")
(command "_circle" "2555.671,948.7" "0.15")
(command "_circle" "2557.921,950.7" "0.075")
(command "_circle" "2557.546,950.7" "0.15")
(command "_circle" "2557.171,950.7" "0.075")
(command "_circle" "2556.796,950.7" "0.075")
(command "_circle" "2556.421,950.7" "0.15")
(command "_circle" "2556.046,950.7" "0.15")
(command "_circle" "2555.671,950.7" "0.15")
(command "_circle" "2557.921,952.7" "0.075")
(command "_circle" "2557.546,952.7" "0.075")
(command "_circle" "2557.171,952.7" "0.15")
(command "_circle" "2556.796,952.7" "0.075")
(command "_circle" "2556.421,952.7" "0.15")
(command "_circle" "2556.046,952.7" "0.15")
(command "_circle" "2555.671,952.7" "0.15")
(command "_circle" "2557.921,954.7" "0.075")
(command "_circle" "2557.546,954.7" "0.15")
(command "_circle" "2557.171,954.7" "0.15")
(command "_circle" "2556.796,954.7" "0.075")
(command "_circle" "2556.421,954.7" "0.15")
(command "_circle" "2556.046,954.7" "0.15")
(command "_circle" "2555.671,954.7" "0.15")
(command "_circle" "2557.921,956.7" "0.075")
(command "_circle" "2557.546,956.7" "0.075")
(command "_circle" "2557.171,956.7" "0.075")
(command "_circle" "2556.796,956.7" "0.15")
(command "_circle" "2556.421,956.7" "0.15")
(command "_circle" "2556.046,956.7" "0.15")
(command "_circle" "2555.671,956.7" "0.15")
(command "_circle" "2557.921,958.7" "0.075")
(command "_circle" "2557.546,958.7" "0.15")
(command "_circle" "2557.171,958.7" "0.075")
(command "_circle" "2556.796,958.7" "0.15")
(command "_circle" "2556.421,958.7" "0.15")
(command "_circle" "2556.046,958.7" "0.15")
(command "_circle" "2555.671,958.7" "0.15")
(command "_circle" "2557.921,960.7" "0.075")
(command "_circle" "2557.546,960.7" "0.075")
(command "_circle" "2557.171,960.7" "0.15")
(command "_circle" "2556.796,960.7" "0.15")
(command "_circle" "2556.421,960.7" "0.15")
(command "_circle" "2556.046,960.7" "0.15")
(command "_circle" "2555.671,960.7" "0.15")
(command "_circle" "2557.921,962.7" "0.075")
(command "_circle" "2557.546,962.7" "0.15")
(command "_circle" "2557.171,962.7" "0.15")
(command "_circle" "2556.796,962.7" "0.15")
(command "_circle" "2556.421,962.7" "0.15")
(command "_circle" "2556.046,962.7" "0.15")
(command "_circle" "2555.671,962.7" "0.15")
(command "_layer" "set" "nitride" "")
(command "_layer" "set" "text" "")
(command-s "_text" "2546.871,963.3" "2" "-90" "a = 370 nm" )
(sssetfirst nil (ssget "_L"))
(if (not (numberp (vl-string-search "Mac" (getvar "platform")))) (c:txtexp))
(command "_layer" "set" "nitride" "")
(command "_layer" "set" "text" "")
(command-s "_text" "2543.871,963.3" "2" "-90" "gap = 270 nm" )
(sssetfirst nil (ssget "_L"))
(if (not (numberp (vl-string-search "Mac" (getvar "platform")))) (c:txtexp))
(command "_layer" "set" "nitride" "")
(command "_layer" "set" "text" "")
(command-s "_text" "2540.871,963.3" "2" "-90" "amplitude = 135.5 nm" )
(sssetfirst nil (ssget "_L"))
(if (not (numberp (vl-string-search "Mac" (getvar "platform")))) (c:txtexp))
(command "_layer" "set" "nitride" "")
(command "_layer" "set" "text" "")
(command-s "_text" "2537.871,963.3" "2" "-90" "start width = 280 nm" )
(sssetfirst nil (ssget "_L"))
(if (not (numberp (vl-string-search "Mac" (getvar "platform")))) (c:txtexp))
(command "_layer" "set" "nitride" "")
(command "_layer" "set" "text" "")
(command-s "_text" "2534.871,963.3" "2" "-90" "width = 294 nm" )
(sssetfirst nil (ssget "_L"))
(if (not (numberp (vl-string-search "Mac" (getvar "platform")))) (c:txtexp))
(command "_layer" "set" "nitride" "")
(command "_layer" "set" "text" "")
(command-s "_text" "2531.871,963.3" "2" "-90" "taper: 15" )
(sssetfirst nil (ssget "_L"))
(if (not (numberp (vl-string-search "Mac" (getvar "platform")))) (c:txtexp))
(command "_layer" "set" "nitride" "")
(command "_layer" "set" "text" "")
(command-s "_text" "2528.871,963.3" "2" "-90" "nominal: 150" )
(sssetfirst nil (ssget "_L"))
(if (not (numberp (vl-string-search "Mac" (getvar "platform")))) (c:txtexp))
(command "_layer" "set" "nitride" "")
(command "_layer" "set" "indicators" "")
(setq coords (list 
(list 2480.415 940) 
(list 2480.415 920) 
(list 2460.415 900) 
(list 2480.415 880) 
(list 2480.415 860) 
(list 2480.415 900) 
(list 2480.415 887.0711) 
(list 2467.4861 900) 
(list 2480.415 912.9289) 
(list 2480.415 900)))
(apply 'command (append '("pline") coords '("c")))
(command "._fillet" "radius" "1" "._fillet" "P" (entlast))
(setq coords (list 
(list 2639.585 940) 
(list 2639.585 920) 
(list 2659.585 900) 
(list 2639.585 880) 
(list 2639.585 860) 
(list 2639.585 900) 
(list 2639.585 887.0711) 
(list 2652.5139 900) 
(list 2639.585 912.9289) 
(list 2639.585 900)))
(apply 'command (append '("pline") coords '("c")))
(command "._fillet" "radius" "1" "._fillet" "P" (entlast))
(command "_layer" "set" "holes" "")
(command "_circle" "2478.0629,914.1124" "0.5")
(command "_circle" "2475.7109,911.7603" "0.5")
(command "_circle" "2473.3588,909.4083" "0.5")
(command "_circle" "2471.0067,907.0562" "0.5")
(command "_circle" "2468.6547,904.7041" "0.5")
(command "_circle" "2466.3026,902.3521" "0.5")
(command "_circle" "2463.9505,900" "0.5")
(command "_circle" "2466.3026,897.6479" "0.5")
(command "_circle" "2468.6547,895.2959" "0.5")
(command "_circle" "2471.0067,892.9438" "0.5")
(command "_circle" "2473.3588,890.5917" "0.5")
(command "_circle" "2475.7109,888.2397" "0.5")
(command "_circle" "2478.0629,885.8876" "0.5")
(command "_circle" "2641.9371,914.1124" "0.5")
(command "_circle" "2644.2891,911.7603" "0.5")
(command "_circle" "2646.6412,909.4083" "0.5")
(command "_circle" "2648.9933,907.0562" "0.5")
(command "_circle" "2651.3453,904.7041" "0.5")
(command "_circle" "2653.6974,902.3521" "0.5")
(command "_circle" "2656.0495,900" "0.5")
(command "_circle" "2653.6974,897.6479" "0.5")
(command "_circle" "2651.3453,895.2959" "0.5")
(command "_circle" "2648.9933,892.9438" "0.5")
(command "_circle" "2646.6412,890.5917" "0.5")
(command "_circle" "2644.2891,888.2397" "0.5")
(command "_circle" "2641.9371,885.8876" "0.5")
(command "_layer" "set" "nitride" "")
(command "_block" "blkcoupler8" "2560,900" coupler8 "")
(command "_insert" "blkcoupler8" "2560,900" "1" "1" "0")
(command "_insert" "blkcoupler8" "2560,900" "1" "1" "180")
(command "_block" "blksinglenanobeam8" "2560,900" singlenanobeam8 "")
(command "_insert" "blksinglenanobeam8" "2560,900" "1" "1" "0")
(command "_insert" "blksinglenanobeam8" "2560,900" "1" "1" "180")
(command "_block" "blkanglednodearray8" "2560,900" anglednodearray8 "")
(command "_insert" "blkanglednodearray8" "2560,900" "1" "1" "0")
(command "_insert" "blkanglednodearray8" "2560,900" "1" "1" "180")
(command "_block" "blkcooledsinglenanobeam8" "2560,900" cooledsinglenanobeam8 "")
(command "_insert" "blkcooledsinglenanobeam8" "2560,900" "1" "1" "0")
(command "_insert" "blkcooledsinglenanobeam8" "2560,900" "1" "1" "180")
(command "_block" "blkyjunction8" "2560,900" yjunction8 "")
(command "_insert" "blkyjunction8" "2560,900" "1" "1" "0")
(command "_insert" "blkyjunction8" "2560,900" "1" "1" "180")
; DRAWING BULGING VEE GROOVE
(command "_layer" "set" "vgroove" "")
(setq coords (list 
(list 2485.415 -605) 
(list 2485.415 0) 
(list 2485.415 0) 
(list 2485.415 1800) 
(list 2485.415 1800) 
(list 2485.415 2405) 
(list 2634.585 2405) 
(list 2634.585 1800) 
(list 2634.585 1800) 
(list 2634.585 0) 
(list 2634.585 0) 
(list 2634.585 -605)))
(apply 'command (append '("pline") coords '("c")))
(command "._fillet" "radius" "0" "._fillet" "P" (entlast))
(command "_layer" "set" "window" "")
(command "_rectangle" "2485.415,-1935" "2634.585,-600")
(command "_rectangle" "2485.415,2400" "2634.585,5300")
(command "_layer" "set" "grid" "")
(command "_rectangle" "2486.415,-1934" "2509.9433,-1909.2133")
(command "_array" "last" "" "R" "75" "3" "25.7867" "24.5283")
(command "_rectangle" "2561,-1934" "2584.5283,-1909.2133")
(command "_array" "last" "" "R" "75" "3" "25.7867" "24.5283")
(command "_rectangle" "2486.415,1" "2509.9433,25.7")
(command "_array" "last" "" "R" "70" "3" "25.7" "24.5283")
(command "_rectangle" "2561,1" "2584.5283,25.7")
(command "_array" "last" "" "R" "70" "3" "25.7" "24.5283")
(command "_rectangle" "2486.415,1801" "2509.9433,1825.9185")
(command "_array" "last" "" "R" "135" "3" "25.9185" "24.5283")
(command "_rectangle" "2561,1801" "2584.5283,1825.9185")
(command "_array" "last" "" "R" "135" "3" "25.9185" "24.5283")
(command "_layer" "set" "vgrooveFDA" "")
(command "_rectangle" "2634.585,-2233" "2485.415,-1933")
(command "_layer" "set" "nitride" "")
(command "_layer" "set" "holes" "")
(command "_circle" "2637.085,331.5" "0.5")
(command "_array" "last" "" "R" "379" "1" "3" "2.5")
(command "_circle" "2482.915,331.5" "0.5")
(command "_array" "last" "" "R" "379" "1" "3" "-2.5")
(command "_layer" "set" "nitride" "")
(command "_layer" "set" "window" "")
(command "_layer" "set" "window" "")
(command "_rectangle" "2639.585,0" "2800.415,1800")
(command "._fillet" "radius" "20" "._fillet" "P" (entlast))
(command "_layer" "set" "grid" "")
(command "_rectangle" "2640.585,1" "2662.4179,25.7")
(command "_array" "last" "" "R" "70" "7" "25.7" "22.8329")
(command "_layer" "set" "nitride" "")
; DRAWING REGION LAYER
(command "_layer" "set" "regionLayer8" "")
(command "_rectangle" "2480,-460" "2640,2260")
(command "_layer" "set" "nitride" "")
(setq coupler8 nil)
(setq singlenanobeam8 nil)
(setq anglednodearray8 nil)
(setq cooledsinglenanobeam8 nil)
(setq yjunction8 nil)
; DEVICE #9
(command "_layer" "set" "window" "")
(command "_circle" "2792.915,-415" "5")
(command "_circle" "2792.915,-402.5" "5")
(command "_circle" "2792.915,-390" "5")
(command "_circle" "2792.915,-377.5" "5")
(command "_circle" "2780.415,-415" "5")
(command "_circle" "2780.415,-402.5" "5")
(command "_circle" "2780.415,-390" "5")
(command "_circle" "2780.415,-377.5" "5")
(command "_circle" "2767.915,-415" "5")
(command "_layer" "set" "nitride" "")
(setq currobj nil)
(setq currobj (ssadd))
; DRAWING COUPLER
(setq coords (list 
(list 2880.0645 -415) 
(list 2880.0645 -413) 
(list 2953.585 -413) 
(list 2953.585 -413) 
(list 2953.9677 -413.0761) 
(list 2954.2921 -413.2929) 
(list 2954.5089 -413.6173) 
(list 2954.585 -414) 
(list 2954.585 -411.8) 
(list 2954.585 -411.8) 
(list 2954.5089 -412.1827) 
(list 2954.2921 -412.5071) 
(list 2953.9677 -412.7239) 
(list 2953.585 -412.8) 
(list 2880.0645 -412.8) 
(list 2880.0645 -410.8) 
(list 2879.9355 -410.8) 
(list 2879.9355 -412.8) 
(list 2806.415 -412.8) 
(list 2806.0323 -412.7239) 
(list 2805.7079 -412.5071) 
(list 2805.4911 -412.1827) 
(list 2805.415 -411.8) 
(list 2805.415 -411.8) 
(list 2805.415 -414) 
(list 2805.4911 -413.6173) 
(list 2805.7079 -413.2929) 
(list 2806.0323 -413.0761) 
(list 2806.415 -413) 
(list 2806.415 -413) 
(list 2879.9355 -413) 
(list 2879.9355 -415)))
(apply 'command (append '("pline") coords '("c")))
(setq currobj (ssadd (entlast) currobj))
(command "._fillet" "radius" "0.3" "._fillet" "P" (entlast))
(command "_layer" "set" "holes" "")
(command "_circle" "2880,-412.9" "0.113")
(setq currobj (ssadd (entlast) currobj))
(command "_layer" "set" "nitride" "")
(command "_layer" "set" "text" "")
(command "_circle" "2879.2,-415" "0.075")
(command "_circle" "2879.2,-414.7" "0.075")
(command "_circle" "2879.2,-414.4" "0.075")
(command "_circle" "2878.9,-415" "0.075")
(command "_circle" "2878.9,-414.7" "0.075")
(command "_circle" "2878.9,-414.4" "0.075")
(command "_circle" "2878.6,-415" "0.075")
(command "_circle" "2878.6,-414.7" "0.075")
(command "_circle" "2878.6,-414.4" "0.075")
(command "_layer" "set" "nitride" "")
(command "_layer" "set" "prebias" "")
(command "_rectangle" "2805.415,-414" "2954.585,-411.8")
(setq currobj (ssadd (entlast) currobj))
(command "_rectangle" "2879.9355,-415" "2880.0645,-410.8")
(setq currobj (ssadd (entlast) currobj))
(command "_layer" "set" "nitride" "")
(setq coupler9 currobj)
(setq currobj nil)
(setq currobj (ssadd))
; DRAWING SINGLE NANOBEAM
(setq coords (list 
(list 2880.0645 -410.8) 
(list 2880.0645 -409.1417) 
(list 2880.0645 -407.4833) 
(list 2880.0645 -405.825) 
(list 2880.0645 -404.1667) 
(list 2880.0645 -402.5083) 
(list 2880.0645 -400.85) 
(list 2880.0645 -399.1917) 
(list 2880.0645 -397.5333) 
(list 2880.0646 -395.875) 
(list 2880.0646 -394.2167) 
(list 2880.0646 -392.5583) 
(list 2880.0646 -390.9) 
(list 2880.0647 -389.2417) 
(list 2880.0647 -387.5833) 
(list 2880.0647 -385.925) 
(list 2880.0648 -384.2667) 
(list 2880.0648 -382.6083) 
(list 2880.0649 -380.95) 
(list 2880.065 -379.2917) 
(list 2880.0651 -377.6333) 
(list 2880.0651 -375.975) 
(list 2880.0652 -374.3167) 
(list 2880.0653 -372.6583) 
(list 2880.0655 -371) 
(list 2880.0656 -369.3417) 
(list 2880.0657 -367.6833) 
(list 2880.0659 -366.025) 
(list 2880.066 -364.3667) 
(list 2880.0662 -362.7083) 
(list 2880.0664 -361.05) 
(list 2880.0666 -359.3917) 
(list 2880.0668 -357.7333) 
(list 2880.067 -356.075) 
(list 2880.0672 -354.4167) 
(list 2880.0675 -352.7583) 
(list 2880.0678 -351.1) 
(list 2880.068 -349.4417) 
(list 2880.0683 -347.7833) 
(list 2880.0686 -346.125) 
(list 2880.069 -344.4667) 
(list 2880.0693 -342.8083) 
(list 2880.0697 -341.15) 
(list 2880.07 -339.4917) 
(list 2880.0704 -337.8333) 
(list 2880.0709 -336.175) 
(list 2880.0713 -334.5167) 
(list 2880.0717 -332.8583) 
(list 2880.0722 -331.2) 
(list 2880.0727 -329.5417) 
(list 2880.0732 -327.8833) 
(list 2880.0738 -326.225) 
(list 2880.0743 -324.5667) 
(list 2880.0749 -322.9083) 
(list 2880.0755 -321.25) 
(list 2880.0761 -319.5917) 
(list 2880.0767 -317.9333) 
(list 2880.0774 -316.275) 
(list 2880.0781 -314.6167) 
(list 2880.0788 -312.9583) 
(list 2880.0796 -311.3) 
(list 2880.0803 -309.6417) 
(list 2880.0811 -307.9833) 
(list 2880.0819 -306.325) 
(list 2880.0828 -304.6667) 
(list 2880.0837 -303.0083) 
(list 2880.0845 -301.35) 
(list 2880.0855 -299.6917) 
(list 2880.0864 -298.0333) 
(list 2880.0874 -296.375) 
(list 2880.0884 -294.7167) 
(list 2880.0895 -293.0583) 
(list 2880.0905 -291.4) 
(list 2880.0916 -289.7417) 
(list 2880.0928 -288.0833) 
(list 2880.0939 -286.425) 
(list 2880.0951 -284.7667) 
(list 2880.0963 -283.1083) 
(list 2880.0976 -281.45) 
(list 2880.0989 -279.7917) 
(list 2880.1002 -278.1333) 
(list 2880.1016 -276.475) 
(list 2880.1029 -274.8167) 
(list 2880.1044 -273.1583) 
(list 2880.1058 -271.5) 
(list 2880.1073 -269.8417) 
(list 2880.1089 -268.1833) 
(list 2880.1104 -266.525) 
(list 2880.112 -264.8667) 
(list 2880.1137 -263.2083) 
(list 2880.1153 -261.55) 
(list 2880.117 -259.8917) 
(list 2880.1188 -258.2333) 
(list 2880.1206 -256.575) 
(list 2880.1224 -254.9167) 
(list 2880.1243 -253.2583) 
(list 2880.1262 -251.6) 
(list 2880.1281 -249.9417) 
(list 2880.1301 -248.2833) 
(list 2880.1322 -246.625) 
(list 2880.1342 -244.9667) 
(list 2880.1363 -243.3083) 
(list 2880.1385 -241.65) 
(list 2880.1407 -239.9917) 
(list 2880.1429 -238.3333) 
(list 2880.1452 -236.675) 
(list 2880.1476 -235.0167) 
(list 2880.1499 -233.3583) 
(list 2880.1523 -231.7) 
(list 2880.1548 -230.0417) 
(list 2880.1573 -228.3833) 
(list 2880.1599 -226.725) 
(list 2880.1625 -225.0667) 
(list 2880.1651 -223.4083) 
(list 2880.1678 -221.75) 
(list 2880.1706 -220.0917) 
(list 2880.1733 -218.4333) 
(list 2880.1762 -216.775) 
(list 2880.1791 -215.1167) 
(list 2880.182 -213.4583) 
(list 2880.185 -211.8) 
(list 2879.815 -211.8) 
(list 2879.818 -213.4583) 
(list 2879.8209 -215.1167) 
(list 2879.8238 -216.775) 
(list 2879.8267 -218.4333) 
(list 2879.8294 -220.0917) 
(list 2879.8322 -221.75) 
(list 2879.8349 -223.4083) 
(list 2879.8375 -225.0667) 
(list 2879.8401 -226.725) 
(list 2879.8427 -228.3833) 
(list 2879.8452 -230.0417) 
(list 2879.8477 -231.7) 
(list 2879.8501 -233.3583) 
(list 2879.8524 -235.0167) 
(list 2879.8548 -236.675) 
(list 2879.8571 -238.3333) 
(list 2879.8593 -239.9917) 
(list 2879.8615 -241.65) 
(list 2879.8637 -243.3083) 
(list 2879.8658 -244.9667) 
(list 2879.8678 -246.625) 
(list 2879.8699 -248.2833) 
(list 2879.8719 -249.9417) 
(list 2879.8738 -251.6) 
(list 2879.8757 -253.2583) 
(list 2879.8776 -254.9167) 
(list 2879.8794 -256.575) 
(list 2879.8812 -258.2333) 
(list 2879.883 -259.8917) 
(list 2879.8847 -261.55) 
(list 2879.8863 -263.2083) 
(list 2879.888 -264.8667) 
(list 2879.8896 -266.525) 
(list 2879.8911 -268.1833) 
(list 2879.8927 -269.8417) 
(list 2879.8942 -271.5) 
(list 2879.8956 -273.1583) 
(list 2879.8971 -274.8167) 
(list 2879.8984 -276.475) 
(list 2879.8998 -278.1333) 
(list 2879.9011 -279.7917) 
(list 2879.9024 -281.45) 
(list 2879.9037 -283.1083) 
(list 2879.9049 -284.7667) 
(list 2879.9061 -286.425) 
(list 2879.9072 -288.0833) 
(list 2879.9084 -289.7417) 
(list 2879.9095 -291.4) 
(list 2879.9105 -293.0583) 
(list 2879.9116 -294.7167) 
(list 2879.9126 -296.375) 
(list 2879.9136 -298.0333) 
(list 2879.9145 -299.6917) 
(list 2879.9155 -301.35) 
(list 2879.9163 -303.0083) 
(list 2879.9172 -304.6667) 
(list 2879.9181 -306.325) 
(list 2879.9189 -307.9833) 
(list 2879.9197 -309.6417) 
(list 2879.9204 -311.3) 
(list 2879.9212 -312.9583) 
(list 2879.9219 -314.6167) 
(list 2879.9226 -316.275) 
(list 2879.9233 -317.9333) 
(list 2879.9239 -319.5917) 
(list 2879.9245 -321.25) 
(list 2879.9251 -322.9083) 
(list 2879.9257 -324.5667) 
(list 2879.9262 -326.225) 
(list 2879.9268 -327.8833) 
(list 2879.9273 -329.5417) 
(list 2879.9278 -331.2) 
(list 2879.9283 -332.8583) 
(list 2879.9287 -334.5167) 
(list 2879.9291 -336.175) 
(list 2879.9296 -337.8333) 
(list 2879.93 -339.4917) 
(list 2879.9303 -341.15) 
(list 2879.9307 -342.8083) 
(list 2879.931 -344.4667) 
(list 2879.9314 -346.125) 
(list 2879.9317 -347.7833) 
(list 2879.932 -349.4417) 
(list 2879.9322 -351.1) 
(list 2879.9325 -352.7583) 
(list 2879.9328 -354.4167) 
(list 2879.933 -356.075) 
(list 2879.9332 -357.7333) 
(list 2879.9334 -359.3917) 
(list 2879.9336 -361.05) 
(list 2879.9338 -362.7083) 
(list 2879.934 -364.3667) 
(list 2879.9341 -366.025) 
(list 2879.9343 -367.6833) 
(list 2879.9344 -369.3417) 
(list 2879.9345 -371) 
(list 2879.9347 -372.6583) 
(list 2879.9348 -374.3167) 
(list 2879.9349 -375.975) 
(list 2879.9349 -377.6333) 
(list 2879.935 -379.2917) 
(list 2879.9351 -380.95) 
(list 2879.9352 -382.6083) 
(list 2879.9352 -384.2667) 
(list 2879.9353 -385.925) 
(list 2879.9353 -387.5833) 
(list 2879.9353 -389.2417) 
(list 2879.9354 -390.9) 
(list 2879.9354 -392.5583) 
(list 2879.9354 -394.2167) 
(list 2879.9354 -395.875) 
(list 2879.9355 -397.5333) 
(list 2879.9355 -399.1917) 
(list 2879.9355 -400.85) 
(list 2879.9355 -402.5083) 
(list 2879.9355 -404.1667) 
(list 2879.9355 -405.825) 
(list 2879.9355 -407.4833) 
(list 2879.9355 -409.1417) 
(list 2879.9355 -410.8)))
(apply 'command (append '("pline") coords '("c")))
(setq currobj (ssadd (entlast) currobj))
(command "_layer" "set" "prebias" "")
(command "_rectangle" "2879.815,-410.8" "2880.185,-211.8")
(setq currobj (ssadd (entlast) currobj))
(command "_layer" "set" "nitride" "")
(setq singlenanobeam9 currobj)
(setq currobj nil)
(setq currobj (ssadd))
; DRAWING NODE ARRAY
(setq coords (list 
(list 2880.185 -211.8) 
(list 2880.5625 -201.8) 
(list 2880.5625 -201.8) 
(list 2880.5625 -200.8) 
(list 2954.585 -212.6864) 
(list 2954.585 -207.7434) 
(list 2880.5625 -197.357) 
(list 2880.5625 -196.357) 
(list 2880.5625 -196.357) 
(list 2880.2625 -186.357) 
(list 2879.7375 -186.357) 
(list 2879.4375 -196.357) 
(list 2879.4375 -196.357) 
(list 2879.4375 -197.357) 
(list 2805.415 -207.7434) 
(list 2805.415 -212.6864) 
(list 2879.4375 -200.8) 
(list 2879.4375 -201.8) 
(list 2879.4375 -201.8) 
(list 2879.815 -211.8)))
(apply 'command (append '("pline") coords '("c")))
(setq currobj (ssadd (entlast) currobj))
(command "_layer" "set" "prebias" "")
(setq coords (list 
(list 2879.4375 -212.6864) 
(list 2879.4375 -200.8) 
(list 2805.415 -212.6864) 
(list 2805.415 -207.7434) 
(list 2879.4375 -197.357) 
(list 2879.4375 -186.357) 
(list 2880.5625 -186.357) 
(list 2880.5625 -197.357) 
(list 2954.585 -207.7434) 
(list 2954.585 -212.6864) 
(list 2880.5625 -200.8) 
(list 2880.5625 -212.6864)))
(apply 'command (append '("pline") coords '("c")))
(setq currobj (ssadd (entlast) currobj))
(command "_layer" "set" "nitride" "")
(command "_layer" "set" "fda1" "")
(setq coords (list 
(list 2880.5625 -200.657) 
(list 2954.585 -212.5434) 
(list 2954.585 -212.3664) 
(list 2880.5625 -200.58)))
(apply 'command (append '("pline") coords '("c")))
(setq currobj (ssadd (entlast) currobj))
(setq coords (list 
(list 2880.5625 -200.437) 
(list 2954.585 -212.2234) 
(list 2954.585 -212.0464) 
(list 2880.5625 -200.36)))
(apply 'command (append '("pline") coords '("c")))
(setq currobj (ssadd (entlast) currobj))
(setq coords (list 
(list 2880.5625 -200.217) 
(list 2954.585 -211.9034) 
(list 2954.585 -211.7264) 
(list 2880.5625 -200.14)))
(apply 'command (append '("pline") coords '("c")))
(setq currobj (ssadd (entlast) currobj))
(setq coords (list 
(list 2880.5625 -199.997) 
(list 2954.585 -211.5834) 
(list 2954.585 -211.4064) 
(list 2880.5625 -199.92)))
(apply 'command (append '("pline") coords '("c")))
(setq currobj (ssadd (entlast) currobj))
(setq coords (list 
(list 2880.5625 -199.777) 
(list 2954.585 -211.2634) 
(list 2954.585 -211.0864) 
(list 2880.5625 -199.7)))
(apply 'command (append '("pline") coords '("c")))
(setq currobj (ssadd (entlast) currobj))
(setq coords (list 
(list 2880.5625 -199.557) 
(list 2954.585 -210.9434) 
(list 2954.585 -210.7664) 
(list 2880.5625 -199.48)))
(apply 'command (append '("pline") coords '("c")))
(setq currobj (ssadd (entlast) currobj))
(setq coords (list 
(list 2880.5625 -199.337) 
(list 2954.585 -210.6234) 
(list 2954.585 -210.4464) 
(list 2880.5625 -199.26)))
(apply 'command (append '("pline") coords '("c")))
(setq currobj (ssadd (entlast) currobj))
(setq coords (list 
(list 2880.5625 -199.117) 
(list 2954.585 -210.3034) 
(list 2954.585 -210.1264) 
(list 2880.5625 -199.04)))
(apply 'command (append '("pline") coords '("c")))
(setq currobj (ssadd (entlast) currobj))
(setq coords (list 
(list 2880.5625 -198.897) 
(list 2954.585 -209.9834) 
(list 2954.585 -209.8064) 
(list 2880.5625 -198.82)))
(apply 'command (append '("pline") coords '("c")))
(setq currobj (ssadd (entlast) currobj))
(setq coords (list 
(list 2880.5625 -198.677) 
(list 2954.585 -209.6634) 
(list 2954.585 -209.4864) 
(list 2880.5625 -198.6)))
(apply 'command (append '("pline") coords '("c")))
(setq currobj (ssadd (entlast) currobj))
(setq coords (list 
(list 2880.5625 -198.457) 
(list 2954.585 -209.3434) 
(list 2954.585 -209.1664) 
(list 2880.5625 -198.38)))
(apply 'command (append '("pline") coords '("c")))
(setq currobj (ssadd (entlast) currobj))
(setq coords (list 
(list 2880.5625 -198.237) 
(list 2954.585 -209.0234) 
(list 2954.585 -208.8464) 
(list 2880.5625 -198.16)))
(apply 'command (append '("pline") coords '("c")))
(setq currobj (ssadd (entlast) currobj))
(setq coords (list 
(list 2880.5625 -198.017) 
(list 2954.585 -208.7034) 
(list 2954.585 -208.5264) 
(list 2880.5625 -197.94)))
(apply 'command (append '("pline") coords '("c")))
(setq currobj (ssadd (entlast) currobj))
(setq coords (list 
(list 2880.5625 -197.797) 
(list 2954.585 -208.3834) 
(list 2954.585 -208.2064) 
(list 2880.5625 -197.72)))
(apply 'command (append '("pline") coords '("c")))
(setq currobj (ssadd (entlast) currobj))
(setq coords (list 
(list 2880.5625 -197.577) 
(list 2954.585 -208.0634) 
(list 2954.585 -207.8864) 
(list 2880.5625 -197.5)))
(apply 'command (append '("pline") coords '("c")))
(setq currobj (ssadd (entlast) currobj))
(setq coords (list 
(list 2879.4375 -197.5) 
(list 2805.415 -207.8864) 
(list 2805.415 -208.0634) 
(list 2879.4375 -197.577)))
(apply 'command (append '("pline") coords '("c")))
(setq currobj (ssadd (entlast) currobj))
(setq coords (list 
(list 2879.4375 -197.72) 
(list 2805.415 -208.2064) 
(list 2805.415 -208.3834) 
(list 2879.4375 -197.797)))
(apply 'command (append '("pline") coords '("c")))
(setq currobj (ssadd (entlast) currobj))
(setq coords (list 
(list 2879.4375 -197.94) 
(list 2805.415 -208.5264) 
(list 2805.415 -208.7034) 
(list 2879.4375 -198.017)))
(apply 'command (append '("pline") coords '("c")))
(setq currobj (ssadd (entlast) currobj))
(setq coords (list 
(list 2879.4375 -198.16) 
(list 2805.415 -208.8464) 
(list 2805.415 -209.0234) 
(list 2879.4375 -198.237)))
(apply 'command (append '("pline") coords '("c")))
(setq currobj (ssadd (entlast) currobj))
(setq coords (list 
(list 2879.4375 -198.38) 
(list 2805.415 -209.1664) 
(list 2805.415 -209.3434) 
(list 2879.4375 -198.457)))
(apply 'command (append '("pline") coords '("c")))
(setq currobj (ssadd (entlast) currobj))
(setq coords (list 
(list 2879.4375 -198.6) 
(list 2805.415 -209.4864) 
(list 2805.415 -209.6634) 
(list 2879.4375 -198.677)))
(apply 'command (append '("pline") coords '("c")))
(setq currobj (ssadd (entlast) currobj))
(setq coords (list 
(list 2879.4375 -198.82) 
(list 2805.415 -209.8064) 
(list 2805.415 -209.9834) 
(list 2879.4375 -198.897)))
(apply 'command (append '("pline") coords '("c")))
(setq currobj (ssadd (entlast) currobj))
(setq coords (list 
(list 2879.4375 -199.04) 
(list 2805.415 -210.1264) 
(list 2805.415 -210.3034) 
(list 2879.4375 -199.117)))
(apply 'command (append '("pline") coords '("c")))
(setq currobj (ssadd (entlast) currobj))
(setq coords (list 
(list 2879.4375 -199.26) 
(list 2805.415 -210.4464) 
(list 2805.415 -210.6234) 
(list 2879.4375 -199.337)))
(apply 'command (append '("pline") coords '("c")))
(setq currobj (ssadd (entlast) currobj))
(setq coords (list 
(list 2879.4375 -199.48) 
(list 2805.415 -210.7664) 
(list 2805.415 -210.9434) 
(list 2879.4375 -199.557)))
(apply 'command (append '("pline") coords '("c")))
(setq currobj (ssadd (entlast) currobj))
(setq coords (list 
(list 2879.4375 -199.7) 
(list 2805.415 -211.0864) 
(list 2805.415 -211.2634) 
(list 2879.4375 -199.777)))
(apply 'command (append '("pline") coords '("c")))
(setq currobj (ssadd (entlast) currobj))
(setq coords (list 
(list 2879.4375 -199.92) 
(list 2805.415 -211.4064) 
(list 2805.415 -211.5834) 
(list 2879.4375 -199.997)))
(apply 'command (append '("pline") coords '("c")))
(setq currobj (ssadd (entlast) currobj))
(setq coords (list 
(list 2879.4375 -200.14) 
(list 2805.415 -211.7264) 
(list 2805.415 -211.9034) 
(list 2879.4375 -200.217)))
(apply 'command (append '("pline") coords '("c")))
(setq currobj (ssadd (entlast) currobj))
(setq coords (list 
(list 2879.4375 -200.36) 
(list 2805.415 -212.0464) 
(list 2805.415 -212.2234) 
(list 2879.4375 -200.437)))
(apply 'command (append '("pline") coords '("c")))
(setq currobj (ssadd (entlast) currobj))
(setq coords (list 
(list 2879.4375 -200.58) 
(list 2805.415 -212.3664) 
(list 2805.415 -212.5434) 
(list 2879.4375 -200.657)))
(apply 'command (append '("pline") coords '("c")))
(setq currobj (ssadd (entlast) currobj))
(command "_layer" "set" "nitride" "")
(command "_layer" "set" "text" "")
(command "_circle" "2878.985,-211.8" "0.075")
(command "_circle" "2878.985,-211.5" "0.075")
(command "_circle" "2878.985,-211.2" "0.075")
(command "_circle" "2878.985,-210.9" "0.075")
(command "_circle" "2878.985,-210.6" "0.075")
(command "_circle" "2878.685,-211.8" "0.075")
(command "_circle" "2878.685,-211.5" "0.075")
(command "_circle" "2878.685,-211.2" "0.075")
(command "_circle" "2878.685,-210.9" "0.075")
(command "_circle" "2878.685,-210.6" "0.075")
(command "_circle" "2878.385,-211.8" "0.075")
(command "_circle" "2878.385,-211.5" "0.075")
(command "_circle" "2878.385,-211.2" "0.075")
(command "_circle" "2878.385,-210.9" "0.075")
(command "_circle" "2878.385,-210.6" "0.075")
(command "_circle" "2878.085,-211.8" "0.075")
(command "_circle" "2878.085,-211.5" "0.075")
(command "_circle" "2878.085,-211.2" "0.075")
(command "_circle" "2878.085,-210.9" "0.075")
(command "_circle" "2878.085,-210.6" "0.075")
(command "_circle" "2877.785,-211.8" "0.075")
(command "_circle" "2877.785,-211.5" "0.075")
(command "_circle" "2877.785,-211.2" "0.075")
(command "_circle" "2877.785,-210.9" "0.075")
(command "_circle" "2877.785,-210.6" "0.075")
(command "_layer" "set" "nitride" "")
(setq anglednodearray9 currobj)
(setq currobj nil)
(setq currobj (ssadd))
; DRAWING COOLED SINGLE NANOBEAM
(setq coords (list 
(list 2880.2625 -186.357) 
(list 2880.2625 -181.357) 
(list 2879.7375 -181.357) 
(list 2879.7375 -186.357)))
(apply 'command (append '("pline") coords '("c")))
(setq currobj (ssadd (entlast) currobj))
(command "_layer" "set" "prebias" "")
(command "_rectangle" "2879.7375,-186.357" "2880.2625,-181.357")
(setq currobj (ssadd (entlast) currobj))
(command "_layer" "set" "nitride" "")
(setq coords (list 
(list 2880.2625 -181.357) 
(list 2880.5625 -171.357) 
(list 2880.5625 -171.357) 
(list 2880.5625 -170.357) 
(list 2954.585 -171.107) 
(list 2954.585 -166.164) 
(list 2880.5625 -166.914) 
(list 2880.5625 -165.914) 
(list 2880.5625 -165.914) 
(list 2880.2625 -155.914) 
(list 2879.7375 -155.914) 
(list 2879.4375 -165.914) 
(list 2879.4375 -165.914) 
(list 2879.4375 -166.914) 
(list 2805.415 -166.164) 
(list 2805.415 -171.107) 
(list 2879.4375 -170.357) 
(list 2879.4375 -171.357) 
(list 2879.4375 -171.357) 
(list 2879.7375 -181.357)))
(apply 'command (append '("pline") coords '("c")))
(setq currobj (ssadd (entlast) currobj))
(command "_layer" "set" "prebias" "")
(setq coords (list 
(list 2879.4375 -181.357) 
(list 2879.4375 -170.357) 
(list 2805.415 -171.107) 
(list 2805.415 -166.164) 
(list 2879.4375 -166.914) 
(list 2879.4375 -155.914) 
(list 2880.5625 -155.914) 
(list 2880.5625 -166.914) 
(list 2954.585 -166.164) 
(list 2954.585 -171.107) 
(list 2880.5625 -170.357) 
(list 2880.5625 -181.357)))
(apply 'command (append '("pline") coords '("c")))
(setq currobj (ssadd (entlast) currobj))
(command "_layer" "set" "nitride" "")
(command "_layer" "set" "fda1" "")
(setq coords (list 
(list 2880.5625 -170.214) 
(list 2954.585 -170.964) 
(list 2954.585 -170.787) 
(list 2880.5625 -170.137)))
(apply 'command (append '("pline") coords '("c")))
(setq currobj (ssadd (entlast) currobj))
(setq coords (list 
(list 2880.5625 -169.994) 
(list 2954.585 -170.644) 
(list 2954.585 -170.467) 
(list 2880.5625 -169.917)))
(apply 'command (append '("pline") coords '("c")))
(setq currobj (ssadd (entlast) currobj))
(setq coords (list 
(list 2880.5625 -169.774) 
(list 2954.585 -170.324) 
(list 2954.585 -170.147) 
(list 2880.5625 -169.697)))
(apply 'command (append '("pline") coords '("c")))
(setq currobj (ssadd (entlast) currobj))
(setq coords (list 
(list 2880.5625 -169.554) 
(list 2954.585 -170.004) 
(list 2954.585 -169.827) 
(list 2880.5625 -169.477)))
(apply 'command (append '("pline") coords '("c")))
(setq currobj (ssadd (entlast) currobj))
(setq coords (list 
(list 2880.5625 -169.334) 
(list 2954.585 -169.684) 
(list 2954.585 -169.507) 
(list 2880.5625 -169.257)))
(apply 'command (append '("pline") coords '("c")))
(setq currobj (ssadd (entlast) currobj))
(setq coords (list 
(list 2880.5625 -169.114) 
(list 2954.585 -169.364) 
(list 2954.585 -169.187) 
(list 2880.5625 -169.037)))
(apply 'command (append '("pline") coords '("c")))
(setq currobj (ssadd (entlast) currobj))
(setq coords (list 
(list 2880.5625 -168.894) 
(list 2954.585 -169.044) 
(list 2954.585 -168.867) 
(list 2880.5625 -168.817)))
(apply 'command (append '("pline") coords '("c")))
(setq currobj (ssadd (entlast) currobj))
(setq coords (list 
(list 2880.5625 -168.674) 
(list 2954.585 -168.724) 
(list 2954.585 -168.547) 
(list 2880.5625 -168.597)))
(apply 'command (append '("pline") coords '("c")))
(setq currobj (ssadd (entlast) currobj))
(setq coords (list 
(list 2880.5625 -168.454) 
(list 2954.585 -168.404) 
(list 2954.585 -168.227) 
(list 2880.5625 -168.377)))
(apply 'command (append '("pline") coords '("c")))
(setq currobj (ssadd (entlast) currobj))
(setq coords (list 
(list 2880.5625 -168.234) 
(list 2954.585 -168.084) 
(list 2954.585 -167.907) 
(list 2880.5625 -168.157)))
(apply 'command (append '("pline") coords '("c")))
(setq currobj (ssadd (entlast) currobj))
(setq coords (list 
(list 2880.5625 -168.014) 
(list 2954.585 -167.764) 
(list 2954.585 -167.587) 
(list 2880.5625 -167.937)))
(apply 'command (append '("pline") coords '("c")))
(setq currobj (ssadd (entlast) currobj))
(setq coords (list 
(list 2880.5625 -167.794) 
(list 2954.585 -167.444) 
(list 2954.585 -167.267) 
(list 2880.5625 -167.717)))
(apply 'command (append '("pline") coords '("c")))
(setq currobj (ssadd (entlast) currobj))
(setq coords (list 
(list 2880.5625 -167.574) 
(list 2954.585 -167.124) 
(list 2954.585 -166.947) 
(list 2880.5625 -167.497)))
(apply 'command (append '("pline") coords '("c")))
(setq currobj (ssadd (entlast) currobj))
(setq coords (list 
(list 2880.5625 -167.354) 
(list 2954.585 -166.804) 
(list 2954.585 -166.627) 
(list 2880.5625 -167.277)))
(apply 'command (append '("pline") coords '("c")))
(setq currobj (ssadd (entlast) currobj))
(setq coords (list 
(list 2880.5625 -167.134) 
(list 2954.585 -166.484) 
(list 2954.585 -166.307) 
(list 2880.5625 -167.057)))
(apply 'command (append '("pline") coords '("c")))
(setq currobj (ssadd (entlast) currobj))
(setq coords (list 
(list 2879.4375 -167.057) 
(list 2805.415 -166.307) 
(list 2805.415 -166.484) 
(list 2879.4375 -167.134)))
(apply 'command (append '("pline") coords '("c")))
(setq currobj (ssadd (entlast) currobj))
(setq coords (list 
(list 2879.4375 -167.277) 
(list 2805.415 -166.627) 
(list 2805.415 -166.804) 
(list 2879.4375 -167.354)))
(apply 'command (append '("pline") coords '("c")))
(setq currobj (ssadd (entlast) currobj))
(setq coords (list 
(list 2879.4375 -167.497) 
(list 2805.415 -166.947) 
(list 2805.415 -167.124) 
(list 2879.4375 -167.574)))
(apply 'command (append '("pline") coords '("c")))
(setq currobj (ssadd (entlast) currobj))
(setq coords (list 
(list 2879.4375 -167.717) 
(list 2805.415 -167.267) 
(list 2805.415 -167.444) 
(list 2879.4375 -167.794)))
(apply 'command (append '("pline") coords '("c")))
(setq currobj (ssadd (entlast) currobj))
(setq coords (list 
(list 2879.4375 -167.937) 
(list 2805.415 -167.587) 
(list 2805.415 -167.764) 
(list 2879.4375 -168.014)))
(apply 'command (append '("pline") coords '("c")))
(setq currobj (ssadd (entlast) currobj))
(setq coords (list 
(list 2879.4375 -168.157) 
(list 2805.415 -167.907) 
(list 2805.415 -168.084) 
(list 2879.4375 -168.234)))
(apply 'command (append '("pline") coords '("c")))
(setq currobj (ssadd (entlast) currobj))
(setq coords (list 
(list 2879.4375 -168.377) 
(list 2805.415 -168.227) 
(list 2805.415 -168.404) 
(list 2879.4375 -168.454)))
(apply 'command (append '("pline") coords '("c")))
(setq currobj (ssadd (entlast) currobj))
(setq coords (list 
(list 2879.4375 -168.597) 
(list 2805.415 -168.547) 
(list 2805.415 -168.724) 
(list 2879.4375 -168.674)))
(apply 'command (append '("pline") coords '("c")))
(setq currobj (ssadd (entlast) currobj))
(setq coords (list 
(list 2879.4375 -168.817) 
(list 2805.415 -168.867) 
(list 2805.415 -169.044) 
(list 2879.4375 -168.894)))
(apply 'command (append '("pline") coords '("c")))
(setq currobj (ssadd (entlast) currobj))
(setq coords (list 
(list 2879.4375 -169.037) 
(list 2805.415 -169.187) 
(list 2805.415 -169.364) 
(list 2879.4375 -169.114)))
(apply 'command (append '("pline") coords '("c")))
(setq currobj (ssadd (entlast) currobj))
(setq coords (list 
(list 2879.4375 -169.257) 
(list 2805.415 -169.507) 
(list 2805.415 -169.684) 
(list 2879.4375 -169.334)))
(apply 'command (append '("pline") coords '("c")))
(setq currobj (ssadd (entlast) currobj))
(setq coords (list 
(list 2879.4375 -169.477) 
(list 2805.415 -169.827) 
(list 2805.415 -170.004) 
(list 2879.4375 -169.554)))
(apply 'command (append '("pline") coords '("c")))
(setq currobj (ssadd (entlast) currobj))
(setq coords (list 
(list 2879.4375 -169.697) 
(list 2805.415 -170.147) 
(list 2805.415 -170.324) 
(list 2879.4375 -169.774)))
(apply 'command (append '("pline") coords '("c")))
(setq currobj (ssadd (entlast) currobj))
(setq coords (list 
(list 2879.4375 -169.917) 
(list 2805.415 -170.467) 
(list 2805.415 -170.644) 
(list 2879.4375 -169.994)))
(apply 'command (append '("pline") coords '("c")))
(setq currobj (ssadd (entlast) currobj))
(setq coords (list 
(list 2879.4375 -170.137) 
(list 2805.415 -170.787) 
(list 2805.415 -170.964) 
(list 2879.4375 -170.214)))
(apply 'command (append '("pline") coords '("c")))
(setq currobj (ssadd (entlast) currobj))
(command "_layer" "set" "nitride" "")
(command "_layer" "set" "text" "")
(command "_circle" "2879.0625,-181.357" "0.075")
(command "_circle" "2879.0625,-181.057" "0.075")
(command "_circle" "2879.0625,-180.757" "0.075")
(command "_circle" "2879.0625,-180.457" "0.075")
(command "_circle" "2879.0625,-180.157" "0.075")
(command "_circle" "2878.7625,-181.357" "0.075")
(command "_circle" "2878.7625,-181.057" "0.075")
(command "_circle" "2878.7625,-180.757" "0.075")
(command "_circle" "2878.7625,-180.457" "0.075")
(command "_circle" "2878.7625,-180.157" "0.075")
(command "_circle" "2878.4625,-181.357" "0.075")
(command "_circle" "2878.4625,-181.057" "0.075")
(command "_circle" "2878.4625,-180.757" "0.075")
(command "_circle" "2878.4625,-180.457" "0.075")
(command "_circle" "2878.4625,-180.157" "0.075")
(command "_circle" "2878.1625,-181.357" "0.075")
(command "_circle" "2878.1625,-181.057" "0.075")
(command "_circle" "2878.1625,-180.757" "0.075")
(command "_circle" "2878.1625,-180.457" "0.075")
(command "_circle" "2878.1625,-180.157" "0.075")
(command "_circle" "2877.8625,-181.357" "0.075")
(command "_circle" "2877.8625,-181.057" "0.075")
(command "_circle" "2877.8625,-180.757" "0.075")
(command "_circle" "2877.8625,-180.457" "0.075")
(command "_circle" "2877.8625,-180.157" "0.075")
(command "_layer" "set" "nitride" "")
(setq coords (list 
(list 2880.2625 -155.914) 
(list 2880.2625 -40.2693) 
(list 2879.7375 -40.2693) 
(list 2879.7375 -155.914)))
(apply 'command (append '("pline") coords '("c")))
(setq currobj (ssadd (entlast) currobj))
(command "_layer" "set" "prebias" "")
(command "_rectangle" "2879.7375,-155.914" "2880.2625,-40.2693")
(setq currobj (ssadd (entlast) currobj))
(command "_layer" "set" "nitride" "")
(setq coords (list 
(list 2880.2625 -40.2693) 
(list 2880.5625 -30.2693) 
(list 2880.5625 -30.2693) 
(list 2880.5625 -29.2693) 
(list 2954.585 -30.0193) 
(list 2954.585 -25.0763) 
(list 2880.5625 -25.8263) 
(list 2880.5625 -24.8263) 
(list 2880.5625 -24.8263) 
(list 2880.2625 -14.8263) 
(list 2879.7375 -14.8263) 
(list 2879.4375 -24.8263) 
(list 2879.4375 -24.8263) 
(list 2879.4375 -25.8263) 
(list 2805.415 -25.0763) 
(list 2805.415 -30.0193) 
(list 2879.4375 -29.2693) 
(list 2879.4375 -30.2693) 
(list 2879.4375 -30.2693) 
(list 2879.7375 -40.2693)))
(apply 'command (append '("pline") coords '("c")))
(setq currobj (ssadd (entlast) currobj))
(command "_layer" "set" "prebias" "")
(setq coords (list 
(list 2879.4375 -40.2693) 
(list 2879.4375 -29.2693) 
(list 2805.415 -30.0193) 
(list 2805.415 -25.0763) 
(list 2879.4375 -25.8263) 
(list 2879.4375 -14.8263) 
(list 2880.5625 -14.8263) 
(list 2880.5625 -25.8263) 
(list 2954.585 -25.0763) 
(list 2954.585 -30.0193) 
(list 2880.5625 -29.2693) 
(list 2880.5625 -40.2693)))
(apply 'command (append '("pline") coords '("c")))
(setq currobj (ssadd (entlast) currobj))
(command "_layer" "set" "nitride" "")
(command "_layer" "set" "fda1" "")
(setq coords (list 
(list 2880.5625 -29.1263) 
(list 2954.585 -29.8763) 
(list 2954.585 -29.6993) 
(list 2880.5625 -29.0493)))
(apply 'command (append '("pline") coords '("c")))
(setq currobj (ssadd (entlast) currobj))
(setq coords (list 
(list 2880.5625 -28.9063) 
(list 2954.585 -29.5563) 
(list 2954.585 -29.3793) 
(list 2880.5625 -28.8293)))
(apply 'command (append '("pline") coords '("c")))
(setq currobj (ssadd (entlast) currobj))
(setq coords (list 
(list 2880.5625 -28.6863) 
(list 2954.585 -29.2363) 
(list 2954.585 -29.0593) 
(list 2880.5625 -28.6093)))
(apply 'command (append '("pline") coords '("c")))
(setq currobj (ssadd (entlast) currobj))
(setq coords (list 
(list 2880.5625 -28.4663) 
(list 2954.585 -28.9163) 
(list 2954.585 -28.7393) 
(list 2880.5625 -28.3893)))
(apply 'command (append '("pline") coords '("c")))
(setq currobj (ssadd (entlast) currobj))
(setq coords (list 
(list 2880.5625 -28.2463) 
(list 2954.585 -28.5963) 
(list 2954.585 -28.4193) 
(list 2880.5625 -28.1693)))
(apply 'command (append '("pline") coords '("c")))
(setq currobj (ssadd (entlast) currobj))
(setq coords (list 
(list 2880.5625 -28.0263) 
(list 2954.585 -28.2763) 
(list 2954.585 -28.0993) 
(list 2880.5625 -27.9493)))
(apply 'command (append '("pline") coords '("c")))
(setq currobj (ssadd (entlast) currobj))
(setq coords (list 
(list 2880.5625 -27.8063) 
(list 2954.585 -27.9563) 
(list 2954.585 -27.7793) 
(list 2880.5625 -27.7293)))
(apply 'command (append '("pline") coords '("c")))
(setq currobj (ssadd (entlast) currobj))
(setq coords (list 
(list 2880.5625 -27.5863) 
(list 2954.585 -27.6363) 
(list 2954.585 -27.4593) 
(list 2880.5625 -27.5093)))
(apply 'command (append '("pline") coords '("c")))
(setq currobj (ssadd (entlast) currobj))
(setq coords (list 
(list 2880.5625 -27.3663) 
(list 2954.585 -27.3163) 
(list 2954.585 -27.1393) 
(list 2880.5625 -27.2893)))
(apply 'command (append '("pline") coords '("c")))
(setq currobj (ssadd (entlast) currobj))
(setq coords (list 
(list 2880.5625 -27.1463) 
(list 2954.585 -26.9963) 
(list 2954.585 -26.8193) 
(list 2880.5625 -27.0693)))
(apply 'command (append '("pline") coords '("c")))
(setq currobj (ssadd (entlast) currobj))
(setq coords (list 
(list 2880.5625 -26.9263) 
(list 2954.585 -26.6763) 
(list 2954.585 -26.4993) 
(list 2880.5625 -26.8493)))
(apply 'command (append '("pline") coords '("c")))
(setq currobj (ssadd (entlast) currobj))
(setq coords (list 
(list 2880.5625 -26.7063) 
(list 2954.585 -26.3563) 
(list 2954.585 -26.1793) 
(list 2880.5625 -26.6293)))
(apply 'command (append '("pline") coords '("c")))
(setq currobj (ssadd (entlast) currobj))
(setq coords (list 
(list 2880.5625 -26.4863) 
(list 2954.585 -26.0363) 
(list 2954.585 -25.8593) 
(list 2880.5625 -26.4093)))
(apply 'command (append '("pline") coords '("c")))
(setq currobj (ssadd (entlast) currobj))
(setq coords (list 
(list 2880.5625 -26.2663) 
(list 2954.585 -25.7163) 
(list 2954.585 -25.5393) 
(list 2880.5625 -26.1893)))
(apply 'command (append '("pline") coords '("c")))
(setq currobj (ssadd (entlast) currobj))
(setq coords (list 
(list 2880.5625 -26.0463) 
(list 2954.585 -25.3963) 
(list 2954.585 -25.2193) 
(list 2880.5625 -25.9693)))
(apply 'command (append '("pline") coords '("c")))
(setq currobj (ssadd (entlast) currobj))
(setq coords (list 
(list 2879.4375 -25.9693) 
(list 2805.415 -25.2193) 
(list 2805.415 -25.3963) 
(list 2879.4375 -26.0463)))
(apply 'command (append '("pline") coords '("c")))
(setq currobj (ssadd (entlast) currobj))
(setq coords (list 
(list 2879.4375 -26.1893) 
(list 2805.415 -25.5393) 
(list 2805.415 -25.7163) 
(list 2879.4375 -26.2663)))
(apply 'command (append '("pline") coords '("c")))
(setq currobj (ssadd (entlast) currobj))
(setq coords (list 
(list 2879.4375 -26.4093) 
(list 2805.415 -25.8593) 
(list 2805.415 -26.0363) 
(list 2879.4375 -26.4863)))
(apply 'command (append '("pline") coords '("c")))
(setq currobj (ssadd (entlast) currobj))
(setq coords (list 
(list 2879.4375 -26.6293) 
(list 2805.415 -26.1793) 
(list 2805.415 -26.3563) 
(list 2879.4375 -26.7063)))
(apply 'command (append '("pline") coords '("c")))
(setq currobj (ssadd (entlast) currobj))
(setq coords (list 
(list 2879.4375 -26.8493) 
(list 2805.415 -26.4993) 
(list 2805.415 -26.6763) 
(list 2879.4375 -26.9263)))
(apply 'command (append '("pline") coords '("c")))
(setq currobj (ssadd (entlast) currobj))
(setq coords (list 
(list 2879.4375 -27.0693) 
(list 2805.415 -26.8193) 
(list 2805.415 -26.9963) 
(list 2879.4375 -27.1463)))
(apply 'command (append '("pline") coords '("c")))
(setq currobj (ssadd (entlast) currobj))
(setq coords (list 
(list 2879.4375 -27.2893) 
(list 2805.415 -27.1393) 
(list 2805.415 -27.3163) 
(list 2879.4375 -27.3663)))
(apply 'command (append '("pline") coords '("c")))
(setq currobj (ssadd (entlast) currobj))
(setq coords (list 
(list 2879.4375 -27.5093) 
(list 2805.415 -27.4593) 
(list 2805.415 -27.6363) 
(list 2879.4375 -27.5863)))
(apply 'command (append '("pline") coords '("c")))
(setq currobj (ssadd (entlast) currobj))
(setq coords (list 
(list 2879.4375 -27.7293) 
(list 2805.415 -27.7793) 
(list 2805.415 -27.9563) 
(list 2879.4375 -27.8063)))
(apply 'command (append '("pline") coords '("c")))
(setq currobj (ssadd (entlast) currobj))
(setq coords (list 
(list 2879.4375 -27.9493) 
(list 2805.415 -28.0993) 
(list 2805.415 -28.2763) 
(list 2879.4375 -28.0263)))
(apply 'command (append '("pline") coords '("c")))
(setq currobj (ssadd (entlast) currobj))
(setq coords (list 
(list 2879.4375 -28.1693) 
(list 2805.415 -28.4193) 
(list 2805.415 -28.5963) 
(list 2879.4375 -28.2463)))
(apply 'command (append '("pline") coords '("c")))
(setq currobj (ssadd (entlast) currobj))
(setq coords (list 
(list 2879.4375 -28.3893) 
(list 2805.415 -28.7393) 
(list 2805.415 -28.9163) 
(list 2879.4375 -28.4663)))
(apply 'command (append '("pline") coords '("c")))
(setq currobj (ssadd (entlast) currobj))
(setq coords (list 
(list 2879.4375 -28.6093) 
(list 2805.415 -29.0593) 
(list 2805.415 -29.2363) 
(list 2879.4375 -28.6863)))
(apply 'command (append '("pline") coords '("c")))
(setq currobj (ssadd (entlast) currobj))
(setq coords (list 
(list 2879.4375 -28.8293) 
(list 2805.415 -29.3793) 
(list 2805.415 -29.5563) 
(list 2879.4375 -28.9063)))
(apply 'command (append '("pline") coords '("c")))
(setq currobj (ssadd (entlast) currobj))
(setq coords (list 
(list 2879.4375 -29.0493) 
(list 2805.415 -29.6993) 
(list 2805.415 -29.8763) 
(list 2879.4375 -29.1263)))
(apply 'command (append '("pline") coords '("c")))
(setq currobj (ssadd (entlast) currobj))
(command "_layer" "set" "nitride" "")
(command "_layer" "set" "text" "")
(command "_circle" "2879.0625,-40.2693" "0.075")
(command "_circle" "2879.0625,-39.9693" "0.075")
(command "_circle" "2879.0625,-39.6693" "0.075")
(command "_circle" "2879.0625,-39.3693" "0.075")
(command "_circle" "2879.0625,-39.0693" "0.075")
(command "_circle" "2878.7625,-40.2693" "0.075")
(command "_circle" "2878.7625,-39.9693" "0.075")
(command "_circle" "2878.7625,-39.6693" "0.075")
(command "_circle" "2878.7625,-39.3693" "0.075")
(command "_circle" "2878.7625,-39.0693" "0.075")
(command "_circle" "2878.4625,-40.2693" "0.075")
(command "_circle" "2878.4625,-39.9693" "0.075")
(command "_circle" "2878.4625,-39.6693" "0.075")
(command "_circle" "2878.4625,-39.3693" "0.075")
(command "_circle" "2878.4625,-39.0693" "0.075")
(command "_circle" "2878.1625,-40.2693" "0.075")
(command "_circle" "2878.1625,-39.9693" "0.075")
(command "_circle" "2878.1625,-39.6693" "0.075")
(command "_circle" "2878.1625,-39.3693" "0.075")
(command "_circle" "2878.1625,-39.0693" "0.075")
(command "_circle" "2877.8625,-40.2693" "0.075")
(command "_circle" "2877.8625,-39.9693" "0.075")
(command "_circle" "2877.8625,-39.6693" "0.075")
(command "_circle" "2877.8625,-39.3693" "0.075")
(command "_circle" "2877.8625,-39.0693" "0.075")
(command "_layer" "set" "nitride" "")
(setq coords (list 
(list 2880.2625 -14.8263) 
(list 2880.2625 100.8184) 
(list 2879.7375 100.8184) 
(list 2879.7375 -14.8263)))
(apply 'command (append '("pline") coords '("c")))
(setq currobj (ssadd (entlast) currobj))
(command "_layer" "set" "prebias" "")
(command "_rectangle" "2879.7375,-14.8263" "2880.2625,100.8184")
(setq currobj (ssadd (entlast) currobj))
(command "_layer" "set" "nitride" "")
(setq coords (list 
(list 2880.2625 100.8184) 
(list 2880.5625 110.8184) 
(list 2880.5625 110.8184) 
(list 2880.5625 111.8184) 
(list 2954.585 111.0684) 
(list 2954.585 116.0114) 
(list 2880.5625 115.2614) 
(list 2880.5625 116.2614) 
(list 2880.5625 116.2614) 
(list 2880.2625 126.2614) 
(list 2879.7375 126.2614) 
(list 2879.4375 116.2614) 
(list 2879.4375 116.2614) 
(list 2879.4375 115.2614) 
(list 2805.415 116.0114) 
(list 2805.415 111.0684) 
(list 2879.4375 111.8184) 
(list 2879.4375 110.8184) 
(list 2879.4375 110.8184) 
(list 2879.7375 100.8184)))
(apply 'command (append '("pline") coords '("c")))
(setq currobj (ssadd (entlast) currobj))
(command "_layer" "set" "prebias" "")
(setq coords (list 
(list 2879.4375 100.8184) 
(list 2879.4375 111.8184) 
(list 2805.415 111.0684) 
(list 2805.415 116.0114) 
(list 2879.4375 115.2614) 
(list 2879.4375 126.2614) 
(list 2880.5625 126.2614) 
(list 2880.5625 115.2614) 
(list 2954.585 116.0114) 
(list 2954.585 111.0684) 
(list 2880.5625 111.8184) 
(list 2880.5625 100.8184)))
(apply 'command (append '("pline") coords '("c")))
(setq currobj (ssadd (entlast) currobj))
(command "_layer" "set" "nitride" "")
(command "_layer" "set" "fda1" "")
(setq coords (list 
(list 2880.5625 111.9614) 
(list 2954.585 111.2114) 
(list 2954.585 111.3884) 
(list 2880.5625 112.0384)))
(apply 'command (append '("pline") coords '("c")))
(setq currobj (ssadd (entlast) currobj))
(setq coords (list 
(list 2880.5625 112.1814) 
(list 2954.585 111.5314) 
(list 2954.585 111.7084) 
(list 2880.5625 112.2584)))
(apply 'command (append '("pline") coords '("c")))
(setq currobj (ssadd (entlast) currobj))
(setq coords (list 
(list 2880.5625 112.4014) 
(list 2954.585 111.8514) 
(list 2954.585 112.0284) 
(list 2880.5625 112.4784)))
(apply 'command (append '("pline") coords '("c")))
(setq currobj (ssadd (entlast) currobj))
(setq coords (list 
(list 2880.5625 112.6214) 
(list 2954.585 112.1714) 
(list 2954.585 112.3484) 
(list 2880.5625 112.6984)))
(apply 'command (append '("pline") coords '("c")))
(setq currobj (ssadd (entlast) currobj))
(setq coords (list 
(list 2880.5625 112.8414) 
(list 2954.585 112.4914) 
(list 2954.585 112.6684) 
(list 2880.5625 112.9184)))
(apply 'command (append '("pline") coords '("c")))
(setq currobj (ssadd (entlast) currobj))
(setq coords (list 
(list 2880.5625 113.0614) 
(list 2954.585 112.8114) 
(list 2954.585 112.9884) 
(list 2880.5625 113.1384)))
(apply 'command (append '("pline") coords '("c")))
(setq currobj (ssadd (entlast) currobj))
(setq coords (list 
(list 2880.5625 113.2814) 
(list 2954.585 113.1314) 
(list 2954.585 113.3084) 
(list 2880.5625 113.3584)))
(apply 'command (append '("pline") coords '("c")))
(setq currobj (ssadd (entlast) currobj))
(setq coords (list 
(list 2880.5625 113.5014) 
(list 2954.585 113.4514) 
(list 2954.585 113.6284) 
(list 2880.5625 113.5784)))
(apply 'command (append '("pline") coords '("c")))
(setq currobj (ssadd (entlast) currobj))
(setq coords (list 
(list 2880.5625 113.7214) 
(list 2954.585 113.7714) 
(list 2954.585 113.9484) 
(list 2880.5625 113.7984)))
(apply 'command (append '("pline") coords '("c")))
(setq currobj (ssadd (entlast) currobj))
(setq coords (list 
(list 2880.5625 113.9414) 
(list 2954.585 114.0914) 
(list 2954.585 114.2684) 
(list 2880.5625 114.0184)))
(apply 'command (append '("pline") coords '("c")))
(setq currobj (ssadd (entlast) currobj))
(setq coords (list 
(list 2880.5625 114.1614) 
(list 2954.585 114.4114) 
(list 2954.585 114.5884) 
(list 2880.5625 114.2384)))
(apply 'command (append '("pline") coords '("c")))
(setq currobj (ssadd (entlast) currobj))
(setq coords (list 
(list 2880.5625 114.3814) 
(list 2954.585 114.7314) 
(list 2954.585 114.9084) 
(list 2880.5625 114.4584)))
(apply 'command (append '("pline") coords '("c")))
(setq currobj (ssadd (entlast) currobj))
(setq coords (list 
(list 2880.5625 114.6014) 
(list 2954.585 115.0514) 
(list 2954.585 115.2284) 
(list 2880.5625 114.6784)))
(apply 'command (append '("pline") coords '("c")))
(setq currobj (ssadd (entlast) currobj))
(setq coords (list 
(list 2880.5625 114.8214) 
(list 2954.585 115.3714) 
(list 2954.585 115.5484) 
(list 2880.5625 114.8984)))
(apply 'command (append '("pline") coords '("c")))
(setq currobj (ssadd (entlast) currobj))
(setq coords (list 
(list 2880.5625 115.0414) 
(list 2954.585 115.6914) 
(list 2954.585 115.8684) 
(list 2880.5625 115.1184)))
(apply 'command (append '("pline") coords '("c")))
(setq currobj (ssadd (entlast) currobj))
(setq coords (list 
(list 2879.4375 115.1184) 
(list 2805.415 115.8684) 
(list 2805.415 115.6914) 
(list 2879.4375 115.0414)))
(apply 'command (append '("pline") coords '("c")))
(setq currobj (ssadd (entlast) currobj))
(setq coords (list 
(list 2879.4375 114.8984) 
(list 2805.415 115.5484) 
(list 2805.415 115.3714) 
(list 2879.4375 114.8214)))
(apply 'command (append '("pline") coords '("c")))
(setq currobj (ssadd (entlast) currobj))
(setq coords (list 
(list 2879.4375 114.6784) 
(list 2805.415 115.2284) 
(list 2805.415 115.0514) 
(list 2879.4375 114.6014)))
(apply 'command (append '("pline") coords '("c")))
(setq currobj (ssadd (entlast) currobj))
(setq coords (list 
(list 2879.4375 114.4584) 
(list 2805.415 114.9084) 
(list 2805.415 114.7314) 
(list 2879.4375 114.3814)))
(apply 'command (append '("pline") coords '("c")))
(setq currobj (ssadd (entlast) currobj))
(setq coords (list 
(list 2879.4375 114.2384) 
(list 2805.415 114.5884) 
(list 2805.415 114.4114) 
(list 2879.4375 114.1614)))
(apply 'command (append '("pline") coords '("c")))
(setq currobj (ssadd (entlast) currobj))
(setq coords (list 
(list 2879.4375 114.0184) 
(list 2805.415 114.2684) 
(list 2805.415 114.0914) 
(list 2879.4375 113.9414)))
(apply 'command (append '("pline") coords '("c")))
(setq currobj (ssadd (entlast) currobj))
(setq coords (list 
(list 2879.4375 113.7984) 
(list 2805.415 113.9484) 
(list 2805.415 113.7714) 
(list 2879.4375 113.7214)))
(apply 'command (append '("pline") coords '("c")))
(setq currobj (ssadd (entlast) currobj))
(setq coords (list 
(list 2879.4375 113.5784) 
(list 2805.415 113.6284) 
(list 2805.415 113.4514) 
(list 2879.4375 113.5014)))
(apply 'command (append '("pline") coords '("c")))
(setq currobj (ssadd (entlast) currobj))
(setq coords (list 
(list 2879.4375 113.3584) 
(list 2805.415 113.3084) 
(list 2805.415 113.1314) 
(list 2879.4375 113.2814)))
(apply 'command (append '("pline") coords '("c")))
(setq currobj (ssadd (entlast) currobj))
(setq coords (list 
(list 2879.4375 113.1384) 
(list 2805.415 112.9884) 
(list 2805.415 112.8114) 
(list 2879.4375 113.0614)))
(apply 'command (append '("pline") coords '("c")))
(setq currobj (ssadd (entlast) currobj))
(setq coords (list 
(list 2879.4375 112.9184) 
(list 2805.415 112.6684) 
(list 2805.415 112.4914) 
(list 2879.4375 112.8414)))
(apply 'command (append '("pline") coords '("c")))
(setq currobj (ssadd (entlast) currobj))
(setq coords (list 
(list 2879.4375 112.6984) 
(list 2805.415 112.3484) 
(list 2805.415 112.1714) 
(list 2879.4375 112.6214)))
(apply 'command (append '("pline") coords '("c")))
(setq currobj (ssadd (entlast) currobj))
(setq coords (list 
(list 2879.4375 112.4784) 
(list 2805.415 112.0284) 
(list 2805.415 111.8514) 
(list 2879.4375 112.4014)))
(apply 'command (append '("pline") coords '("c")))
(setq currobj (ssadd (entlast) currobj))
(setq coords (list 
(list 2879.4375 112.2584) 
(list 2805.415 111.7084) 
(list 2805.415 111.5314) 
(list 2879.4375 112.1814)))
(apply 'command (append '("pline") coords '("c")))
(setq currobj (ssadd (entlast) currobj))
(setq coords (list 
(list 2879.4375 112.0384) 
(list 2805.415 111.3884) 
(list 2805.415 111.2114) 
(list 2879.4375 111.9614)))
(apply 'command (append '("pline") coords '("c")))
(setq currobj (ssadd (entlast) currobj))
(command "_layer" "set" "nitride" "")
(command "_layer" "set" "text" "")
(command "_circle" "2879.0625,100.8184" "0.075")
(command "_circle" "2879.0625,101.1184" "0.075")
(command "_circle" "2879.0625,101.4184" "0.075")
(command "_circle" "2879.0625,101.7184" "0.075")
(command "_circle" "2879.0625,102.0184" "0.075")
(command "_circle" "2878.7625,100.8184" "0.075")
(command "_circle" "2878.7625,101.1184" "0.075")
(command "_circle" "2878.7625,101.4184" "0.075")
(command "_circle" "2878.7625,101.7184" "0.075")
(command "_circle" "2878.7625,102.0184" "0.075")
(command "_circle" "2878.4625,100.8184" "0.075")
(command "_circle" "2878.4625,101.1184" "0.075")
(command "_circle" "2878.4625,101.4184" "0.075")
(command "_circle" "2878.4625,101.7184" "0.075")
(command "_circle" "2878.4625,102.0184" "0.075")
(command "_circle" "2878.1625,100.8184" "0.075")
(command "_circle" "2878.1625,101.1184" "0.075")
(command "_circle" "2878.1625,101.4184" "0.075")
(command "_circle" "2878.1625,101.7184" "0.075")
(command "_circle" "2878.1625,102.0184" "0.075")
(command "_circle" "2877.8625,100.8184" "0.075")
(command "_circle" "2877.8625,101.1184" "0.075")
(command "_circle" "2877.8625,101.4184" "0.075")
(command "_circle" "2877.8625,101.7184" "0.075")
(command "_circle" "2877.8625,102.0184" "0.075")
(command "_layer" "set" "nitride" "")
(setq coords (list 
(list 2880.2625 126.2614) 
(list 2880.2625 241.9061) 
(list 2879.7375 241.9061) 
(list 2879.7375 126.2614)))
(apply 'command (append '("pline") coords '("c")))
(setq currobj (ssadd (entlast) currobj))
(command "_layer" "set" "prebias" "")
(command "_rectangle" "2879.7375,126.2614" "2880.2625,241.9061")
(setq currobj (ssadd (entlast) currobj))
(command "_layer" "set" "nitride" "")
(setq coords (list 
(list 2880.2625 241.9061) 
(list 2880.5625 251.9061) 
(list 2880.5625 251.9061) 
(list 2880.5625 252.9061) 
(list 2954.585 252.1561) 
(list 2954.585 257.0991) 
(list 2880.5625 256.3491) 
(list 2880.5625 257.3491) 
(list 2880.5625 257.3491) 
(list 2880.2625 267.3491) 
(list 2879.7375 267.3491) 
(list 2879.4375 257.3491) 
(list 2879.4375 257.3491) 
(list 2879.4375 256.3491) 
(list 2805.415 257.0991) 
(list 2805.415 252.1561) 
(list 2879.4375 252.9061) 
(list 2879.4375 251.9061) 
(list 2879.4375 251.9061) 
(list 2879.7375 241.9061)))
(apply 'command (append '("pline") coords '("c")))
(setq currobj (ssadd (entlast) currobj))
(command "_layer" "set" "prebias" "")
(setq coords (list 
(list 2879.4375 241.9061) 
(list 2879.4375 252.9061) 
(list 2805.415 252.1561) 
(list 2805.415 257.0991) 
(list 2879.4375 256.3491) 
(list 2879.4375 267.3491) 
(list 2880.5625 267.3491) 
(list 2880.5625 256.3491) 
(list 2954.585 257.0991) 
(list 2954.585 252.1561) 
(list 2880.5625 252.9061) 
(list 2880.5625 241.9061)))
(apply 'command (append '("pline") coords '("c")))
(setq currobj (ssadd (entlast) currobj))
(command "_layer" "set" "nitride" "")
(command "_layer" "set" "fda1" "")
(setq coords (list 
(list 2880.5625 253.0491) 
(list 2954.585 252.2991) 
(list 2954.585 252.4761) 
(list 2880.5625 253.1261)))
(apply 'command (append '("pline") coords '("c")))
(setq currobj (ssadd (entlast) currobj))
(setq coords (list 
(list 2880.5625 253.2691) 
(list 2954.585 252.6191) 
(list 2954.585 252.7961) 
(list 2880.5625 253.3461)))
(apply 'command (append '("pline") coords '("c")))
(setq currobj (ssadd (entlast) currobj))
(setq coords (list 
(list 2880.5625 253.4891) 
(list 2954.585 252.9391) 
(list 2954.585 253.1161) 
(list 2880.5625 253.5661)))
(apply 'command (append '("pline") coords '("c")))
(setq currobj (ssadd (entlast) currobj))
(setq coords (list 
(list 2880.5625 253.7091) 
(list 2954.585 253.2591) 
(list 2954.585 253.4361) 
(list 2880.5625 253.7861)))
(apply 'command (append '("pline") coords '("c")))
(setq currobj (ssadd (entlast) currobj))
(setq coords (list 
(list 2880.5625 253.9291) 
(list 2954.585 253.5791) 
(list 2954.585 253.7561) 
(list 2880.5625 254.0061)))
(apply 'command (append '("pline") coords '("c")))
(setq currobj (ssadd (entlast) currobj))
(setq coords (list 
(list 2880.5625 254.1491) 
(list 2954.585 253.8991) 
(list 2954.585 254.0761) 
(list 2880.5625 254.2261)))
(apply 'command (append '("pline") coords '("c")))
(setq currobj (ssadd (entlast) currobj))
(setq coords (list 
(list 2880.5625 254.3691) 
(list 2954.585 254.2191) 
(list 2954.585 254.3961) 
(list 2880.5625 254.4461)))
(apply 'command (append '("pline") coords '("c")))
(setq currobj (ssadd (entlast) currobj))
(setq coords (list 
(list 2880.5625 254.5891) 
(list 2954.585 254.5391) 
(list 2954.585 254.7161) 
(list 2880.5625 254.6661)))
(apply 'command (append '("pline") coords '("c")))
(setq currobj (ssadd (entlast) currobj))
(setq coords (list 
(list 2880.5625 254.8091) 
(list 2954.585 254.8591) 
(list 2954.585 255.0361) 
(list 2880.5625 254.8861)))
(apply 'command (append '("pline") coords '("c")))
(setq currobj (ssadd (entlast) currobj))
(setq coords (list 
(list 2880.5625 255.0291) 
(list 2954.585 255.1791) 
(list 2954.585 255.3561) 
(list 2880.5625 255.1061)))
(apply 'command (append '("pline") coords '("c")))
(setq currobj (ssadd (entlast) currobj))
(setq coords (list 
(list 2880.5625 255.2491) 
(list 2954.585 255.4991) 
(list 2954.585 255.6761) 
(list 2880.5625 255.3261)))
(apply 'command (append '("pline") coords '("c")))
(setq currobj (ssadd (entlast) currobj))
(setq coords (list 
(list 2880.5625 255.4691) 
(list 2954.585 255.8191) 
(list 2954.585 255.9961) 
(list 2880.5625 255.5461)))
(apply 'command (append '("pline") coords '("c")))
(setq currobj (ssadd (entlast) currobj))
(setq coords (list 
(list 2880.5625 255.6891) 
(list 2954.585 256.1391) 
(list 2954.585 256.3161) 
(list 2880.5625 255.7661)))
(apply 'command (append '("pline") coords '("c")))
(setq currobj (ssadd (entlast) currobj))
(setq coords (list 
(list 2880.5625 255.9091) 
(list 2954.585 256.4591) 
(list 2954.585 256.6361) 
(list 2880.5625 255.9861)))
(apply 'command (append '("pline") coords '("c")))
(setq currobj (ssadd (entlast) currobj))
(setq coords (list 
(list 2880.5625 256.1291) 
(list 2954.585 256.7791) 
(list 2954.585 256.9561) 
(list 2880.5625 256.2061)))
(apply 'command (append '("pline") coords '("c")))
(setq currobj (ssadd (entlast) currobj))
(setq coords (list 
(list 2879.4375 256.2061) 
(list 2805.415 256.9561) 
(list 2805.415 256.7791) 
(list 2879.4375 256.1291)))
(apply 'command (append '("pline") coords '("c")))
(setq currobj (ssadd (entlast) currobj))
(setq coords (list 
(list 2879.4375 255.9861) 
(list 2805.415 256.6361) 
(list 2805.415 256.4591) 
(list 2879.4375 255.9091)))
(apply 'command (append '("pline") coords '("c")))
(setq currobj (ssadd (entlast) currobj))
(setq coords (list 
(list 2879.4375 255.7661) 
(list 2805.415 256.3161) 
(list 2805.415 256.1391) 
(list 2879.4375 255.6891)))
(apply 'command (append '("pline") coords '("c")))
(setq currobj (ssadd (entlast) currobj))
(setq coords (list 
(list 2879.4375 255.5461) 
(list 2805.415 255.9961) 
(list 2805.415 255.8191) 
(list 2879.4375 255.4691)))
(apply 'command (append '("pline") coords '("c")))
(setq currobj (ssadd (entlast) currobj))
(setq coords (list 
(list 2879.4375 255.3261) 
(list 2805.415 255.6761) 
(list 2805.415 255.4991) 
(list 2879.4375 255.2491)))
(apply 'command (append '("pline") coords '("c")))
(setq currobj (ssadd (entlast) currobj))
(setq coords (list 
(list 2879.4375 255.1061) 
(list 2805.415 255.3561) 
(list 2805.415 255.1791) 
(list 2879.4375 255.0291)))
(apply 'command (append '("pline") coords '("c")))
(setq currobj (ssadd (entlast) currobj))
(setq coords (list 
(list 2879.4375 254.8861) 
(list 2805.415 255.0361) 
(list 2805.415 254.8591) 
(list 2879.4375 254.8091)))
(apply 'command (append '("pline") coords '("c")))
(setq currobj (ssadd (entlast) currobj))
(setq coords (list 
(list 2879.4375 254.6661) 
(list 2805.415 254.7161) 
(list 2805.415 254.5391) 
(list 2879.4375 254.5891)))
(apply 'command (append '("pline") coords '("c")))
(setq currobj (ssadd (entlast) currobj))
(setq coords (list 
(list 2879.4375 254.4461) 
(list 2805.415 254.3961) 
(list 2805.415 254.2191) 
(list 2879.4375 254.3691)))
(apply 'command (append '("pline") coords '("c")))
(setq currobj (ssadd (entlast) currobj))
(setq coords (list 
(list 2879.4375 254.2261) 
(list 2805.415 254.0761) 
(list 2805.415 253.8991) 
(list 2879.4375 254.1491)))
(apply 'command (append '("pline") coords '("c")))
(setq currobj (ssadd (entlast) currobj))
(setq coords (list 
(list 2879.4375 254.0061) 
(list 2805.415 253.7561) 
(list 2805.415 253.5791) 
(list 2879.4375 253.9291)))
(apply 'command (append '("pline") coords '("c")))
(setq currobj (ssadd (entlast) currobj))
(setq coords (list 
(list 2879.4375 253.7861) 
(list 2805.415 253.4361) 
(list 2805.415 253.2591) 
(list 2879.4375 253.7091)))
(apply 'command (append '("pline") coords '("c")))
(setq currobj (ssadd (entlast) currobj))
(setq coords (list 
(list 2879.4375 253.5661) 
(list 2805.415 253.1161) 
(list 2805.415 252.9391) 
(list 2879.4375 253.4891)))
(apply 'command (append '("pline") coords '("c")))
(setq currobj (ssadd (entlast) currobj))
(setq coords (list 
(list 2879.4375 253.3461) 
(list 2805.415 252.7961) 
(list 2805.415 252.6191) 
(list 2879.4375 253.2691)))
(apply 'command (append '("pline") coords '("c")))
(setq currobj (ssadd (entlast) currobj))
(setq coords (list 
(list 2879.4375 253.1261) 
(list 2805.415 252.4761) 
(list 2805.415 252.2991) 
(list 2879.4375 253.0491)))
(apply 'command (append '("pline") coords '("c")))
(setq currobj (ssadd (entlast) currobj))
(command "_layer" "set" "nitride" "")
(command "_layer" "set" "text" "")
(command "_circle" "2879.0625,241.9061" "0.075")
(command "_circle" "2879.0625,242.2061" "0.075")
(command "_circle" "2879.0625,242.5061" "0.075")
(command "_circle" "2879.0625,242.8061" "0.075")
(command "_circle" "2879.0625,243.1061" "0.075")
(command "_circle" "2878.7625,241.9061" "0.075")
(command "_circle" "2878.7625,242.2061" "0.075")
(command "_circle" "2878.7625,242.5061" "0.075")
(command "_circle" "2878.7625,242.8061" "0.075")
(command "_circle" "2878.7625,243.1061" "0.075")
(command "_circle" "2878.4625,241.9061" "0.075")
(command "_circle" "2878.4625,242.2061" "0.075")
(command "_circle" "2878.4625,242.5061" "0.075")
(command "_circle" "2878.4625,242.8061" "0.075")
(command "_circle" "2878.4625,243.1061" "0.075")
(command "_circle" "2878.1625,241.9061" "0.075")
(command "_circle" "2878.1625,242.2061" "0.075")
(command "_circle" "2878.1625,242.5061" "0.075")
(command "_circle" "2878.1625,242.8061" "0.075")
(command "_circle" "2878.1625,243.1061" "0.075")
(command "_circle" "2877.8625,241.9061" "0.075")
(command "_circle" "2877.8625,242.2061" "0.075")
(command "_circle" "2877.8625,242.5061" "0.075")
(command "_circle" "2877.8625,242.8061" "0.075")
(command "_circle" "2877.8625,243.1061" "0.075")
(command "_layer" "set" "nitride" "")
(setq coords (list 
(list 2880.2625 267.3491) 
(list 2880.2625 382.9939) 
(list 2879.7375 382.9939) 
(list 2879.7375 267.3491)))
(apply 'command (append '("pline") coords '("c")))
(setq currobj (ssadd (entlast) currobj))
(command "_layer" "set" "prebias" "")
(command "_rectangle" "2879.7375,267.3491" "2880.2625,382.9939")
(setq currobj (ssadd (entlast) currobj))
(command "_layer" "set" "nitride" "")
(setq coords (list 
(list 2880.2625 382.9939) 
(list 2880.5625 392.9939) 
(list 2880.5625 392.9939) 
(list 2880.5625 393.9939) 
(list 2954.585 393.2439) 
(list 2954.585 398.1869) 
(list 2880.5625 397.4369) 
(list 2880.5625 398.4369) 
(list 2880.5625 398.4369) 
(list 2880.2625 408.4369) 
(list 2879.7375 408.4369) 
(list 2879.4375 398.4369) 
(list 2879.4375 398.4369) 
(list 2879.4375 397.4369) 
(list 2805.415 398.1869) 
(list 2805.415 393.2439) 
(list 2879.4375 393.9939) 
(list 2879.4375 392.9939) 
(list 2879.4375 392.9939) 
(list 2879.7375 382.9939)))
(apply 'command (append '("pline") coords '("c")))
(setq currobj (ssadd (entlast) currobj))
(command "_layer" "set" "prebias" "")
(setq coords (list 
(list 2879.4375 382.9939) 
(list 2879.4375 393.9939) 
(list 2805.415 393.2439) 
(list 2805.415 398.1869) 
(list 2879.4375 397.4369) 
(list 2879.4375 408.4369) 
(list 2880.5625 408.4369) 
(list 2880.5625 397.4369) 
(list 2954.585 398.1869) 
(list 2954.585 393.2439) 
(list 2880.5625 393.9939) 
(list 2880.5625 382.9939)))
(apply 'command (append '("pline") coords '("c")))
(setq currobj (ssadd (entlast) currobj))
(command "_layer" "set" "nitride" "")
(command "_layer" "set" "fda1" "")
(setq coords (list 
(list 2880.5625 394.1369) 
(list 2954.585 393.3869) 
(list 2954.585 393.5639) 
(list 2880.5625 394.2139)))
(apply 'command (append '("pline") coords '("c")))
(setq currobj (ssadd (entlast) currobj))
(setq coords (list 
(list 2880.5625 394.3569) 
(list 2954.585 393.7069) 
(list 2954.585 393.8839) 
(list 2880.5625 394.4339)))
(apply 'command (append '("pline") coords '("c")))
(setq currobj (ssadd (entlast) currobj))
(setq coords (list 
(list 2880.5625 394.5769) 
(list 2954.585 394.0269) 
(list 2954.585 394.2039) 
(list 2880.5625 394.6539)))
(apply 'command (append '("pline") coords '("c")))
(setq currobj (ssadd (entlast) currobj))
(setq coords (list 
(list 2880.5625 394.7969) 
(list 2954.585 394.3469) 
(list 2954.585 394.5239) 
(list 2880.5625 394.8739)))
(apply 'command (append '("pline") coords '("c")))
(setq currobj (ssadd (entlast) currobj))
(setq coords (list 
(list 2880.5625 395.0169) 
(list 2954.585 394.6669) 
(list 2954.585 394.8439) 
(list 2880.5625 395.0939)))
(apply 'command (append '("pline") coords '("c")))
(setq currobj (ssadd (entlast) currobj))
(setq coords (list 
(list 2880.5625 395.2369) 
(list 2954.585 394.9869) 
(list 2954.585 395.1639) 
(list 2880.5625 395.3139)))
(apply 'command (append '("pline") coords '("c")))
(setq currobj (ssadd (entlast) currobj))
(setq coords (list 
(list 2880.5625 395.4569) 
(list 2954.585 395.3069) 
(list 2954.585 395.4839) 
(list 2880.5625 395.5339)))
(apply 'command (append '("pline") coords '("c")))
(setq currobj (ssadd (entlast) currobj))
(setq coords (list 
(list 2880.5625 395.6769) 
(list 2954.585 395.6269) 
(list 2954.585 395.8039) 
(list 2880.5625 395.7539)))
(apply 'command (append '("pline") coords '("c")))
(setq currobj (ssadd (entlast) currobj))
(setq coords (list 
(list 2880.5625 395.8969) 
(list 2954.585 395.9469) 
(list 2954.585 396.1239) 
(list 2880.5625 395.9739)))
(apply 'command (append '("pline") coords '("c")))
(setq currobj (ssadd (entlast) currobj))
(setq coords (list 
(list 2880.5625 396.1169) 
(list 2954.585 396.2669) 
(list 2954.585 396.4439) 
(list 2880.5625 396.1939)))
(apply 'command (append '("pline") coords '("c")))
(setq currobj (ssadd (entlast) currobj))
(setq coords (list 
(list 2880.5625 396.3369) 
(list 2954.585 396.5869) 
(list 2954.585 396.7639) 
(list 2880.5625 396.4139)))
(apply 'command (append '("pline") coords '("c")))
(setq currobj (ssadd (entlast) currobj))
(setq coords (list 
(list 2880.5625 396.5569) 
(list 2954.585 396.9069) 
(list 2954.585 397.0839) 
(list 2880.5625 396.6339)))
(apply 'command (append '("pline") coords '("c")))
(setq currobj (ssadd (entlast) currobj))
(setq coords (list 
(list 2880.5625 396.7769) 
(list 2954.585 397.2269) 
(list 2954.585 397.4039) 
(list 2880.5625 396.8539)))
(apply 'command (append '("pline") coords '("c")))
(setq currobj (ssadd (entlast) currobj))
(setq coords (list 
(list 2880.5625 396.9969) 
(list 2954.585 397.5469) 
(list 2954.585 397.7239) 
(list 2880.5625 397.0739)))
(apply 'command (append '("pline") coords '("c")))
(setq currobj (ssadd (entlast) currobj))
(setq coords (list 
(list 2880.5625 397.2169) 
(list 2954.585 397.8669) 
(list 2954.585 398.0439) 
(list 2880.5625 397.2939)))
(apply 'command (append '("pline") coords '("c")))
(setq currobj (ssadd (entlast) currobj))
(setq coords (list 
(list 2879.4375 397.2939) 
(list 2805.415 398.0439) 
(list 2805.415 397.8669) 
(list 2879.4375 397.2169)))
(apply 'command (append '("pline") coords '("c")))
(setq currobj (ssadd (entlast) currobj))
(setq coords (list 
(list 2879.4375 397.0739) 
(list 2805.415 397.7239) 
(list 2805.415 397.5469) 
(list 2879.4375 396.9969)))
(apply 'command (append '("pline") coords '("c")))
(setq currobj (ssadd (entlast) currobj))
(setq coords (list 
(list 2879.4375 396.8539) 
(list 2805.415 397.4039) 
(list 2805.415 397.2269) 
(list 2879.4375 396.7769)))
(apply 'command (append '("pline") coords '("c")))
(setq currobj (ssadd (entlast) currobj))
(setq coords (list 
(list 2879.4375 396.6339) 
(list 2805.415 397.0839) 
(list 2805.415 396.9069) 
(list 2879.4375 396.5569)))
(apply 'command (append '("pline") coords '("c")))
(setq currobj (ssadd (entlast) currobj))
(setq coords (list 
(list 2879.4375 396.4139) 
(list 2805.415 396.7639) 
(list 2805.415 396.5869) 
(list 2879.4375 396.3369)))
(apply 'command (append '("pline") coords '("c")))
(setq currobj (ssadd (entlast) currobj))
(setq coords (list 
(list 2879.4375 396.1939) 
(list 2805.415 396.4439) 
(list 2805.415 396.2669) 
(list 2879.4375 396.1169)))
(apply 'command (append '("pline") coords '("c")))
(setq currobj (ssadd (entlast) currobj))
(setq coords (list 
(list 2879.4375 395.9739) 
(list 2805.415 396.1239) 
(list 2805.415 395.9469) 
(list 2879.4375 395.8969)))
(apply 'command (append '("pline") coords '("c")))
(setq currobj (ssadd (entlast) currobj))
(setq coords (list 
(list 2879.4375 395.7539) 
(list 2805.415 395.8039) 
(list 2805.415 395.6269) 
(list 2879.4375 395.6769)))
(apply 'command (append '("pline") coords '("c")))
(setq currobj (ssadd (entlast) currobj))
(setq coords (list 
(list 2879.4375 395.5339) 
(list 2805.415 395.4839) 
(list 2805.415 395.3069) 
(list 2879.4375 395.4569)))
(apply 'command (append '("pline") coords '("c")))
(setq currobj (ssadd (entlast) currobj))
(setq coords (list 
(list 2879.4375 395.3139) 
(list 2805.415 395.1639) 
(list 2805.415 394.9869) 
(list 2879.4375 395.2369)))
(apply 'command (append '("pline") coords '("c")))
(setq currobj (ssadd (entlast) currobj))
(setq coords (list 
(list 2879.4375 395.0939) 
(list 2805.415 394.8439) 
(list 2805.415 394.6669) 
(list 2879.4375 395.0169)))
(apply 'command (append '("pline") coords '("c")))
(setq currobj (ssadd (entlast) currobj))
(setq coords (list 
(list 2879.4375 394.8739) 
(list 2805.415 394.5239) 
(list 2805.415 394.3469) 
(list 2879.4375 394.7969)))
(apply 'command (append '("pline") coords '("c")))
(setq currobj (ssadd (entlast) currobj))
(setq coords (list 
(list 2879.4375 394.6539) 
(list 2805.415 394.2039) 
(list 2805.415 394.0269) 
(list 2879.4375 394.5769)))
(apply 'command (append '("pline") coords '("c")))
(setq currobj (ssadd (entlast) currobj))
(setq coords (list 
(list 2879.4375 394.4339) 
(list 2805.415 393.8839) 
(list 2805.415 393.7069) 
(list 2879.4375 394.3569)))
(apply 'command (append '("pline") coords '("c")))
(setq currobj (ssadd (entlast) currobj))
(setq coords (list 
(list 2879.4375 394.2139) 
(list 2805.415 393.5639) 
(list 2805.415 393.3869) 
(list 2879.4375 394.1369)))
(apply 'command (append '("pline") coords '("c")))
(setq currobj (ssadd (entlast) currobj))
(command "_layer" "set" "nitride" "")
(command "_layer" "set" "text" "")
(command "_circle" "2879.0625,382.9939" "0.075")
(command "_circle" "2879.0625,383.2939" "0.075")
(command "_circle" "2879.0625,383.5939" "0.075")
(command "_circle" "2879.0625,383.8939" "0.075")
(command "_circle" "2879.0625,384.1939" "0.075")
(command "_circle" "2878.7625,382.9939" "0.075")
(command "_circle" "2878.7625,383.2939" "0.075")
(command "_circle" "2878.7625,383.5939" "0.075")
(command "_circle" "2878.7625,383.8939" "0.075")
(command "_circle" "2878.7625,384.1939" "0.075")
(command "_circle" "2878.4625,382.9939" "0.075")
(command "_circle" "2878.4625,383.2939" "0.075")
(command "_circle" "2878.4625,383.5939" "0.075")
(command "_circle" "2878.4625,383.8939" "0.075")
(command "_circle" "2878.4625,384.1939" "0.075")
(command "_circle" "2878.1625,382.9939" "0.075")
(command "_circle" "2878.1625,383.2939" "0.075")
(command "_circle" "2878.1625,383.5939" "0.075")
(command "_circle" "2878.1625,383.8939" "0.075")
(command "_circle" "2878.1625,384.1939" "0.075")
(command "_circle" "2877.8625,382.9939" "0.075")
(command "_circle" "2877.8625,383.2939" "0.075")
(command "_circle" "2877.8625,383.5939" "0.075")
(command "_circle" "2877.8625,383.8939" "0.075")
(command "_circle" "2877.8625,384.1939" "0.075")
(command "_layer" "set" "nitride" "")
(setq coords (list 
(list 2880.2625 408.4369) 
(list 2880.2625 524.0816) 
(list 2879.7375 524.0816) 
(list 2879.7375 408.4369)))
(apply 'command (append '("pline") coords '("c")))
(setq currobj (ssadd (entlast) currobj))
(command "_layer" "set" "prebias" "")
(command "_rectangle" "2879.7375,408.4369" "2880.2625,524.0816")
(setq currobj (ssadd (entlast) currobj))
(command "_layer" "set" "nitride" "")
(setq coords (list 
(list 2880.2625 524.0816) 
(list 2880.5625 534.0816) 
(list 2880.5625 534.0816) 
(list 2880.5625 535.0816) 
(list 2954.585 534.3316) 
(list 2954.585 539.2746) 
(list 2880.5625 538.5246) 
(list 2880.5625 539.5246) 
(list 2880.5625 539.5246) 
(list 2880.2625 549.5246) 
(list 2879.7375 549.5246) 
(list 2879.4375 539.5246) 
(list 2879.4375 539.5246) 
(list 2879.4375 538.5246) 
(list 2805.415 539.2746) 
(list 2805.415 534.3316) 
(list 2879.4375 535.0816) 
(list 2879.4375 534.0816) 
(list 2879.4375 534.0816) 
(list 2879.7375 524.0816)))
(apply 'command (append '("pline") coords '("c")))
(setq currobj (ssadd (entlast) currobj))
(command "_layer" "set" "prebias" "")
(setq coords (list 
(list 2879.4375 524.0816) 
(list 2879.4375 535.0816) 
(list 2805.415 534.3316) 
(list 2805.415 539.2746) 
(list 2879.4375 538.5246) 
(list 2879.4375 549.5246) 
(list 2880.5625 549.5246) 
(list 2880.5625 538.5246) 
(list 2954.585 539.2746) 
(list 2954.585 534.3316) 
(list 2880.5625 535.0816) 
(list 2880.5625 524.0816)))
(apply 'command (append '("pline") coords '("c")))
(setq currobj (ssadd (entlast) currobj))
(command "_layer" "set" "nitride" "")
(command "_layer" "set" "fda1" "")
(setq coords (list 
(list 2880.5625 535.2246) 
(list 2954.585 534.4746) 
(list 2954.585 534.6516) 
(list 2880.5625 535.3016)))
(apply 'command (append '("pline") coords '("c")))
(setq currobj (ssadd (entlast) currobj))
(setq coords (list 
(list 2880.5625 535.4446) 
(list 2954.585 534.7946) 
(list 2954.585 534.9716) 
(list 2880.5625 535.5216)))
(apply 'command (append '("pline") coords '("c")))
(setq currobj (ssadd (entlast) currobj))
(setq coords (list 
(list 2880.5625 535.6646) 
(list 2954.585 535.1146) 
(list 2954.585 535.2916) 
(list 2880.5625 535.7416)))
(apply 'command (append '("pline") coords '("c")))
(setq currobj (ssadd (entlast) currobj))
(setq coords (list 
(list 2880.5625 535.8846) 
(list 2954.585 535.4346) 
(list 2954.585 535.6116) 
(list 2880.5625 535.9616)))
(apply 'command (append '("pline") coords '("c")))
(setq currobj (ssadd (entlast) currobj))
(setq coords (list 
(list 2880.5625 536.1046) 
(list 2954.585 535.7546) 
(list 2954.585 535.9316) 
(list 2880.5625 536.1816)))
(apply 'command (append '("pline") coords '("c")))
(setq currobj (ssadd (entlast) currobj))
(setq coords (list 
(list 2880.5625 536.3246) 
(list 2954.585 536.0746) 
(list 2954.585 536.2516) 
(list 2880.5625 536.4016)))
(apply 'command (append '("pline") coords '("c")))
(setq currobj (ssadd (entlast) currobj))
(setq coords (list 
(list 2880.5625 536.5446) 
(list 2954.585 536.3946) 
(list 2954.585 536.5716) 
(list 2880.5625 536.6216)))
(apply 'command (append '("pline") coords '("c")))
(setq currobj (ssadd (entlast) currobj))
(setq coords (list 
(list 2880.5625 536.7646) 
(list 2954.585 536.7146) 
(list 2954.585 536.8916) 
(list 2880.5625 536.8416)))
(apply 'command (append '("pline") coords '("c")))
(setq currobj (ssadd (entlast) currobj))
(setq coords (list 
(list 2880.5625 536.9846) 
(list 2954.585 537.0346) 
(list 2954.585 537.2116) 
(list 2880.5625 537.0616)))
(apply 'command (append '("pline") coords '("c")))
(setq currobj (ssadd (entlast) currobj))
(setq coords (list 
(list 2880.5625 537.2046) 
(list 2954.585 537.3546) 
(list 2954.585 537.5316) 
(list 2880.5625 537.2816)))
(apply 'command (append '("pline") coords '("c")))
(setq currobj (ssadd (entlast) currobj))
(setq coords (list 
(list 2880.5625 537.4246) 
(list 2954.585 537.6746) 
(list 2954.585 537.8516) 
(list 2880.5625 537.5016)))
(apply 'command (append '("pline") coords '("c")))
(setq currobj (ssadd (entlast) currobj))
(setq coords (list 
(list 2880.5625 537.6446) 
(list 2954.585 537.9946) 
(list 2954.585 538.1716) 
(list 2880.5625 537.7216)))
(apply 'command (append '("pline") coords '("c")))
(setq currobj (ssadd (entlast) currobj))
(setq coords (list 
(list 2880.5625 537.8646) 
(list 2954.585 538.3146) 
(list 2954.585 538.4916) 
(list 2880.5625 537.9416)))
(apply 'command (append '("pline") coords '("c")))
(setq currobj (ssadd (entlast) currobj))
(setq coords (list 
(list 2880.5625 538.0846) 
(list 2954.585 538.6346) 
(list 2954.585 538.8116) 
(list 2880.5625 538.1616)))
(apply 'command (append '("pline") coords '("c")))
(setq currobj (ssadd (entlast) currobj))
(setq coords (list 
(list 2880.5625 538.3046) 
(list 2954.585 538.9546) 
(list 2954.585 539.1316) 
(list 2880.5625 538.3816)))
(apply 'command (append '("pline") coords '("c")))
(setq currobj (ssadd (entlast) currobj))
(setq coords (list 
(list 2879.4375 538.3816) 
(list 2805.415 539.1316) 
(list 2805.415 538.9546) 
(list 2879.4375 538.3046)))
(apply 'command (append '("pline") coords '("c")))
(setq currobj (ssadd (entlast) currobj))
(setq coords (list 
(list 2879.4375 538.1616) 
(list 2805.415 538.8116) 
(list 2805.415 538.6346) 
(list 2879.4375 538.0846)))
(apply 'command (append '("pline") coords '("c")))
(setq currobj (ssadd (entlast) currobj))
(setq coords (list 
(list 2879.4375 537.9416) 
(list 2805.415 538.4916) 
(list 2805.415 538.3146) 
(list 2879.4375 537.8646)))
(apply 'command (append '("pline") coords '("c")))
(setq currobj (ssadd (entlast) currobj))
(setq coords (list 
(list 2879.4375 537.7216) 
(list 2805.415 538.1716) 
(list 2805.415 537.9946) 
(list 2879.4375 537.6446)))
(apply 'command (append '("pline") coords '("c")))
(setq currobj (ssadd (entlast) currobj))
(setq coords (list 
(list 2879.4375 537.5016) 
(list 2805.415 537.8516) 
(list 2805.415 537.6746) 
(list 2879.4375 537.4246)))
(apply 'command (append '("pline") coords '("c")))
(setq currobj (ssadd (entlast) currobj))
(setq coords (list 
(list 2879.4375 537.2816) 
(list 2805.415 537.5316) 
(list 2805.415 537.3546) 
(list 2879.4375 537.2046)))
(apply 'command (append '("pline") coords '("c")))
(setq currobj (ssadd (entlast) currobj))
(setq coords (list 
(list 2879.4375 537.0616) 
(list 2805.415 537.2116) 
(list 2805.415 537.0346) 
(list 2879.4375 536.9846)))
(apply 'command (append '("pline") coords '("c")))
(setq currobj (ssadd (entlast) currobj))
(setq coords (list 
(list 2879.4375 536.8416) 
(list 2805.415 536.8916) 
(list 2805.415 536.7146) 
(list 2879.4375 536.7646)))
(apply 'command (append '("pline") coords '("c")))
(setq currobj (ssadd (entlast) currobj))
(setq coords (list 
(list 2879.4375 536.6216) 
(list 2805.415 536.5716) 
(list 2805.415 536.3946) 
(list 2879.4375 536.5446)))
(apply 'command (append '("pline") coords '("c")))
(setq currobj (ssadd (entlast) currobj))
(setq coords (list 
(list 2879.4375 536.4016) 
(list 2805.415 536.2516) 
(list 2805.415 536.0746) 
(list 2879.4375 536.3246)))
(apply 'command (append '("pline") coords '("c")))
(setq currobj (ssadd (entlast) currobj))
(setq coords (list 
(list 2879.4375 536.1816) 
(list 2805.415 535.9316) 
(list 2805.415 535.7546) 
(list 2879.4375 536.1046)))
(apply 'command (append '("pline") coords '("c")))
(setq currobj (ssadd (entlast) currobj))
(setq coords (list 
(list 2879.4375 535.9616) 
(list 2805.415 535.6116) 
(list 2805.415 535.4346) 
(list 2879.4375 535.8846)))
(apply 'command (append '("pline") coords '("c")))
(setq currobj (ssadd (entlast) currobj))
(setq coords (list 
(list 2879.4375 535.7416) 
(list 2805.415 535.2916) 
(list 2805.415 535.1146) 
(list 2879.4375 535.6646)))
(apply 'command (append '("pline") coords '("c")))
(setq currobj (ssadd (entlast) currobj))
(setq coords (list 
(list 2879.4375 535.5216) 
(list 2805.415 534.9716) 
(list 2805.415 534.7946) 
(list 2879.4375 535.4446)))
(apply 'command (append '("pline") coords '("c")))
(setq currobj (ssadd (entlast) currobj))
(setq coords (list 
(list 2879.4375 535.3016) 
(list 2805.415 534.6516) 
(list 2805.415 534.4746) 
(list 2879.4375 535.2246)))
(apply 'command (append '("pline") coords '("c")))
(setq currobj (ssadd (entlast) currobj))
(command "_layer" "set" "nitride" "")
(command "_layer" "set" "text" "")
(command "_circle" "2879.0625,524.0816" "0.075")
(command "_circle" "2879.0625,524.3816" "0.075")
(command "_circle" "2879.0625,524.6816" "0.075")
(command "_circle" "2879.0625,524.9816" "0.075")
(command "_circle" "2879.0625,525.2816" "0.075")
(command "_circle" "2878.7625,524.0816" "0.075")
(command "_circle" "2878.7625,524.3816" "0.075")
(command "_circle" "2878.7625,524.6816" "0.075")
(command "_circle" "2878.7625,524.9816" "0.075")
(command "_circle" "2878.7625,525.2816" "0.075")
(command "_circle" "2878.4625,524.0816" "0.075")
(command "_circle" "2878.4625,524.3816" "0.075")
(command "_circle" "2878.4625,524.6816" "0.075")
(command "_circle" "2878.4625,524.9816" "0.075")
(command "_circle" "2878.4625,525.2816" "0.075")
(command "_circle" "2878.1625,524.0816" "0.075")
(command "_circle" "2878.1625,524.3816" "0.075")
(command "_circle" "2878.1625,524.6816" "0.075")
(command "_circle" "2878.1625,524.9816" "0.075")
(command "_circle" "2878.1625,525.2816" "0.075")
(command "_circle" "2877.8625,524.0816" "0.075")
(command "_circle" "2877.8625,524.3816" "0.075")
(command "_circle" "2877.8625,524.6816" "0.075")
(command "_circle" "2877.8625,524.9816" "0.075")
(command "_circle" "2877.8625,525.2816" "0.075")
(command "_layer" "set" "nitride" "")
(setq coords (list 
(list 2880.2625 549.5246) 
(list 2880.2625 665.1693) 
(list 2879.7375 665.1693) 
(list 2879.7375 549.5246)))
(apply 'command (append '("pline") coords '("c")))
(setq currobj (ssadd (entlast) currobj))
(command "_layer" "set" "prebias" "")
(command "_rectangle" "2879.7375,549.5246" "2880.2625,665.1693")
(setq currobj (ssadd (entlast) currobj))
(command "_layer" "set" "nitride" "")
(setq coords (list 
(list 2880.2625 665.1693) 
(list 2880.5625 675.1693) 
(list 2880.5625 675.1693) 
(list 2880.5625 676.1693) 
(list 2954.585 675.4193) 
(list 2954.585 680.3623) 
(list 2880.5625 679.6123) 
(list 2880.5625 680.6123) 
(list 2880.5625 680.6123) 
(list 2880.2625 690.6123) 
(list 2879.7375 690.6123) 
(list 2879.4375 680.6123) 
(list 2879.4375 680.6123) 
(list 2879.4375 679.6123) 
(list 2805.415 680.3623) 
(list 2805.415 675.4193) 
(list 2879.4375 676.1693) 
(list 2879.4375 675.1693) 
(list 2879.4375 675.1693) 
(list 2879.7375 665.1693)))
(apply 'command (append '("pline") coords '("c")))
(setq currobj (ssadd (entlast) currobj))
(command "_layer" "set" "prebias" "")
(setq coords (list 
(list 2879.4375 665.1693) 
(list 2879.4375 676.1693) 
(list 2805.415 675.4193) 
(list 2805.415 680.3623) 
(list 2879.4375 679.6123) 
(list 2879.4375 690.6123) 
(list 2880.5625 690.6123) 
(list 2880.5625 679.6123) 
(list 2954.585 680.3623) 
(list 2954.585 675.4193) 
(list 2880.5625 676.1693) 
(list 2880.5625 665.1693)))
(apply 'command (append '("pline") coords '("c")))
(setq currobj (ssadd (entlast) currobj))
(command "_layer" "set" "nitride" "")
(command "_layer" "set" "fda1" "")
(setq coords (list 
(list 2880.5625 676.3123) 
(list 2954.585 675.5623) 
(list 2954.585 675.7393) 
(list 2880.5625 676.3893)))
(apply 'command (append '("pline") coords '("c")))
(setq currobj (ssadd (entlast) currobj))
(setq coords (list 
(list 2880.5625 676.5323) 
(list 2954.585 675.8823) 
(list 2954.585 676.0593) 
(list 2880.5625 676.6093)))
(apply 'command (append '("pline") coords '("c")))
(setq currobj (ssadd (entlast) currobj))
(setq coords (list 
(list 2880.5625 676.7523) 
(list 2954.585 676.2023) 
(list 2954.585 676.3793) 
(list 2880.5625 676.8293)))
(apply 'command (append '("pline") coords '("c")))
(setq currobj (ssadd (entlast) currobj))
(setq coords (list 
(list 2880.5625 676.9723) 
(list 2954.585 676.5223) 
(list 2954.585 676.6993) 
(list 2880.5625 677.0493)))
(apply 'command (append '("pline") coords '("c")))
(setq currobj (ssadd (entlast) currobj))
(setq coords (list 
(list 2880.5625 677.1923) 
(list 2954.585 676.8423) 
(list 2954.585 677.0193) 
(list 2880.5625 677.2693)))
(apply 'command (append '("pline") coords '("c")))
(setq currobj (ssadd (entlast) currobj))
(setq coords (list 
(list 2880.5625 677.4123) 
(list 2954.585 677.1623) 
(list 2954.585 677.3393) 
(list 2880.5625 677.4893)))
(apply 'command (append '("pline") coords '("c")))
(setq currobj (ssadd (entlast) currobj))
(setq coords (list 
(list 2880.5625 677.6323) 
(list 2954.585 677.4823) 
(list 2954.585 677.6593) 
(list 2880.5625 677.7093)))
(apply 'command (append '("pline") coords '("c")))
(setq currobj (ssadd (entlast) currobj))
(setq coords (list 
(list 2880.5625 677.8523) 
(list 2954.585 677.8023) 
(list 2954.585 677.9793) 
(list 2880.5625 677.9293)))
(apply 'command (append '("pline") coords '("c")))
(setq currobj (ssadd (entlast) currobj))
(setq coords (list 
(list 2880.5625 678.0723) 
(list 2954.585 678.1223) 
(list 2954.585 678.2993) 
(list 2880.5625 678.1493)))
(apply 'command (append '("pline") coords '("c")))
(setq currobj (ssadd (entlast) currobj))
(setq coords (list 
(list 2880.5625 678.2923) 
(list 2954.585 678.4423) 
(list 2954.585 678.6193) 
(list 2880.5625 678.3693)))
(apply 'command (append '("pline") coords '("c")))
(setq currobj (ssadd (entlast) currobj))
(setq coords (list 
(list 2880.5625 678.5123) 
(list 2954.585 678.7623) 
(list 2954.585 678.9393) 
(list 2880.5625 678.5893)))
(apply 'command (append '("pline") coords '("c")))
(setq currobj (ssadd (entlast) currobj))
(setq coords (list 
(list 2880.5625 678.7323) 
(list 2954.585 679.0823) 
(list 2954.585 679.2593) 
(list 2880.5625 678.8093)))
(apply 'command (append '("pline") coords '("c")))
(setq currobj (ssadd (entlast) currobj))
(setq coords (list 
(list 2880.5625 678.9523) 
(list 2954.585 679.4023) 
(list 2954.585 679.5793) 
(list 2880.5625 679.0293)))
(apply 'command (append '("pline") coords '("c")))
(setq currobj (ssadd (entlast) currobj))
(setq coords (list 
(list 2880.5625 679.1723) 
(list 2954.585 679.7223) 
(list 2954.585 679.8993) 
(list 2880.5625 679.2493)))
(apply 'command (append '("pline") coords '("c")))
(setq currobj (ssadd (entlast) currobj))
(setq coords (list 
(list 2880.5625 679.3923) 
(list 2954.585 680.0423) 
(list 2954.585 680.2193) 
(list 2880.5625 679.4693)))
(apply 'command (append '("pline") coords '("c")))
(setq currobj (ssadd (entlast) currobj))
(setq coords (list 
(list 2879.4375 679.4693) 
(list 2805.415 680.2193) 
(list 2805.415 680.0423) 
(list 2879.4375 679.3923)))
(apply 'command (append '("pline") coords '("c")))
(setq currobj (ssadd (entlast) currobj))
(setq coords (list 
(list 2879.4375 679.2493) 
(list 2805.415 679.8993) 
(list 2805.415 679.7223) 
(list 2879.4375 679.1723)))
(apply 'command (append '("pline") coords '("c")))
(setq currobj (ssadd (entlast) currobj))
(setq coords (list 
(list 2879.4375 679.0293) 
(list 2805.415 679.5793) 
(list 2805.415 679.4023) 
(list 2879.4375 678.9523)))
(apply 'command (append '("pline") coords '("c")))
(setq currobj (ssadd (entlast) currobj))
(setq coords (list 
(list 2879.4375 678.8093) 
(list 2805.415 679.2593) 
(list 2805.415 679.0823) 
(list 2879.4375 678.7323)))
(apply 'command (append '("pline") coords '("c")))
(setq currobj (ssadd (entlast) currobj))
(setq coords (list 
(list 2879.4375 678.5893) 
(list 2805.415 678.9393) 
(list 2805.415 678.7623) 
(list 2879.4375 678.5123)))
(apply 'command (append '("pline") coords '("c")))
(setq currobj (ssadd (entlast) currobj))
(setq coords (list 
(list 2879.4375 678.3693) 
(list 2805.415 678.6193) 
(list 2805.415 678.4423) 
(list 2879.4375 678.2923)))
(apply 'command (append '("pline") coords '("c")))
(setq currobj (ssadd (entlast) currobj))
(setq coords (list 
(list 2879.4375 678.1493) 
(list 2805.415 678.2993) 
(list 2805.415 678.1223) 
(list 2879.4375 678.0723)))
(apply 'command (append '("pline") coords '("c")))
(setq currobj (ssadd (entlast) currobj))
(setq coords (list 
(list 2879.4375 677.9293) 
(list 2805.415 677.9793) 
(list 2805.415 677.8023) 
(list 2879.4375 677.8523)))
(apply 'command (append '("pline") coords '("c")))
(setq currobj (ssadd (entlast) currobj))
(setq coords (list 
(list 2879.4375 677.7093) 
(list 2805.415 677.6593) 
(list 2805.415 677.4823) 
(list 2879.4375 677.6323)))
(apply 'command (append '("pline") coords '("c")))
(setq currobj (ssadd (entlast) currobj))
(setq coords (list 
(list 2879.4375 677.4893) 
(list 2805.415 677.3393) 
(list 2805.415 677.1623) 
(list 2879.4375 677.4123)))
(apply 'command (append '("pline") coords '("c")))
(setq currobj (ssadd (entlast) currobj))
(setq coords (list 
(list 2879.4375 677.2693) 
(list 2805.415 677.0193) 
(list 2805.415 676.8423) 
(list 2879.4375 677.1923)))
(apply 'command (append '("pline") coords '("c")))
(setq currobj (ssadd (entlast) currobj))
(setq coords (list 
(list 2879.4375 677.0493) 
(list 2805.415 676.6993) 
(list 2805.415 676.5223) 
(list 2879.4375 676.9723)))
(apply 'command (append '("pline") coords '("c")))
(setq currobj (ssadd (entlast) currobj))
(setq coords (list 
(list 2879.4375 676.8293) 
(list 2805.415 676.3793) 
(list 2805.415 676.2023) 
(list 2879.4375 676.7523)))
(apply 'command (append '("pline") coords '("c")))
(setq currobj (ssadd (entlast) currobj))
(setq coords (list 
(list 2879.4375 676.6093) 
(list 2805.415 676.0593) 
(list 2805.415 675.8823) 
(list 2879.4375 676.5323)))
(apply 'command (append '("pline") coords '("c")))
(setq currobj (ssadd (entlast) currobj))
(setq coords (list 
(list 2879.4375 676.3893) 
(list 2805.415 675.7393) 
(list 2805.415 675.5623) 
(list 2879.4375 676.3123)))
(apply 'command (append '("pline") coords '("c")))
(setq currobj (ssadd (entlast) currobj))
(command "_layer" "set" "nitride" "")
(command "_layer" "set" "text" "")
(command "_circle" "2879.0625,665.1693" "0.075")
(command "_circle" "2879.0625,665.4693" "0.075")
(command "_circle" "2879.0625,665.7693" "0.075")
(command "_circle" "2879.0625,666.0693" "0.075")
(command "_circle" "2879.0625,666.3693" "0.075")
(command "_circle" "2878.7625,665.1693" "0.075")
(command "_circle" "2878.7625,665.4693" "0.075")
(command "_circle" "2878.7625,665.7693" "0.075")
(command "_circle" "2878.7625,666.0693" "0.075")
(command "_circle" "2878.7625,666.3693" "0.075")
(command "_circle" "2878.4625,665.1693" "0.075")
(command "_circle" "2878.4625,665.4693" "0.075")
(command "_circle" "2878.4625,665.7693" "0.075")
(command "_circle" "2878.4625,666.0693" "0.075")
(command "_circle" "2878.4625,666.3693" "0.075")
(command "_circle" "2878.1625,665.1693" "0.075")
(command "_circle" "2878.1625,665.4693" "0.075")
(command "_circle" "2878.1625,665.7693" "0.075")
(command "_circle" "2878.1625,666.0693" "0.075")
(command "_circle" "2878.1625,666.3693" "0.075")
(command "_circle" "2877.8625,665.1693" "0.075")
(command "_circle" "2877.8625,665.4693" "0.075")
(command "_circle" "2877.8625,665.7693" "0.075")
(command "_circle" "2877.8625,666.0693" "0.075")
(command "_circle" "2877.8625,666.3693" "0.075")
(command "_layer" "set" "nitride" "")
(setq coords (list 
(list 2880.2625 690.6123) 
(list 2880.2625 806.257) 
(list 2879.7375 806.257) 
(list 2879.7375 690.6123)))
(apply 'command (append '("pline") coords '("c")))
(setq currobj (ssadd (entlast) currobj))
(command "_layer" "set" "prebias" "")
(command "_rectangle" "2879.7375,690.6123" "2880.2625,806.257")
(setq currobj (ssadd (entlast) currobj))
(command "_layer" "set" "nitride" "")
(setq coords (list 
(list 2880.2625 806.257) 
(list 2880.5625 816.257) 
(list 2880.5625 816.257) 
(list 2880.5625 817.257) 
(list 2954.585 816.507) 
(list 2954.585 821.45) 
(list 2880.5625 820.7) 
(list 2880.5625 821.7) 
(list 2880.5625 821.7) 
(list 2880.2625 831.7) 
(list 2879.7375 831.7) 
(list 2879.4375 821.7) 
(list 2879.4375 821.7) 
(list 2879.4375 820.7) 
(list 2805.415 821.45) 
(list 2805.415 816.507) 
(list 2879.4375 817.257) 
(list 2879.4375 816.257) 
(list 2879.4375 816.257) 
(list 2879.7375 806.257)))
(apply 'command (append '("pline") coords '("c")))
(setq currobj (ssadd (entlast) currobj))
(command "_layer" "set" "prebias" "")
(setq coords (list 
(list 2879.4375 806.257) 
(list 2879.4375 817.257) 
(list 2805.415 816.507) 
(list 2805.415 821.45) 
(list 2879.4375 820.7) 
(list 2879.4375 831.7) 
(list 2880.5625 831.7) 
(list 2880.5625 820.7) 
(list 2954.585 821.45) 
(list 2954.585 816.507) 
(list 2880.5625 817.257) 
(list 2880.5625 806.257)))
(apply 'command (append '("pline") coords '("c")))
(setq currobj (ssadd (entlast) currobj))
(command "_layer" "set" "nitride" "")
(command "_layer" "set" "fda1" "")
(setq coords (list 
(list 2880.5625 817.4) 
(list 2954.585 816.65) 
(list 2954.585 816.827) 
(list 2880.5625 817.477)))
(apply 'command (append '("pline") coords '("c")))
(setq currobj (ssadd (entlast) currobj))
(setq coords (list 
(list 2880.5625 817.62) 
(list 2954.585 816.97) 
(list 2954.585 817.147) 
(list 2880.5625 817.697)))
(apply 'command (append '("pline") coords '("c")))
(setq currobj (ssadd (entlast) currobj))
(setq coords (list 
(list 2880.5625 817.84) 
(list 2954.585 817.29) 
(list 2954.585 817.467) 
(list 2880.5625 817.917)))
(apply 'command (append '("pline") coords '("c")))
(setq currobj (ssadd (entlast) currobj))
(setq coords (list 
(list 2880.5625 818.06) 
(list 2954.585 817.61) 
(list 2954.585 817.787) 
(list 2880.5625 818.137)))
(apply 'command (append '("pline") coords '("c")))
(setq currobj (ssadd (entlast) currobj))
(setq coords (list 
(list 2880.5625 818.28) 
(list 2954.585 817.93) 
(list 2954.585 818.107) 
(list 2880.5625 818.357)))
(apply 'command (append '("pline") coords '("c")))
(setq currobj (ssadd (entlast) currobj))
(setq coords (list 
(list 2880.5625 818.5) 
(list 2954.585 818.25) 
(list 2954.585 818.427) 
(list 2880.5625 818.577)))
(apply 'command (append '("pline") coords '("c")))
(setq currobj (ssadd (entlast) currobj))
(setq coords (list 
(list 2880.5625 818.72) 
(list 2954.585 818.57) 
(list 2954.585 818.747) 
(list 2880.5625 818.797)))
(apply 'command (append '("pline") coords '("c")))
(setq currobj (ssadd (entlast) currobj))
(setq coords (list 
(list 2880.5625 818.94) 
(list 2954.585 818.89) 
(list 2954.585 819.067) 
(list 2880.5625 819.017)))
(apply 'command (append '("pline") coords '("c")))
(setq currobj (ssadd (entlast) currobj))
(setq coords (list 
(list 2880.5625 819.16) 
(list 2954.585 819.21) 
(list 2954.585 819.387) 
(list 2880.5625 819.237)))
(apply 'command (append '("pline") coords '("c")))
(setq currobj (ssadd (entlast) currobj))
(setq coords (list 
(list 2880.5625 819.38) 
(list 2954.585 819.53) 
(list 2954.585 819.707) 
(list 2880.5625 819.457)))
(apply 'command (append '("pline") coords '("c")))
(setq currobj (ssadd (entlast) currobj))
(setq coords (list 
(list 2880.5625 819.6) 
(list 2954.585 819.85) 
(list 2954.585 820.027) 
(list 2880.5625 819.677)))
(apply 'command (append '("pline") coords '("c")))
(setq currobj (ssadd (entlast) currobj))
(setq coords (list 
(list 2880.5625 819.82) 
(list 2954.585 820.17) 
(list 2954.585 820.347) 
(list 2880.5625 819.897)))
(apply 'command (append '("pline") coords '("c")))
(setq currobj (ssadd (entlast) currobj))
(setq coords (list 
(list 2880.5625 820.04) 
(list 2954.585 820.49) 
(list 2954.585 820.667) 
(list 2880.5625 820.117)))
(apply 'command (append '("pline") coords '("c")))
(setq currobj (ssadd (entlast) currobj))
(setq coords (list 
(list 2880.5625 820.26) 
(list 2954.585 820.81) 
(list 2954.585 820.987) 
(list 2880.5625 820.337)))
(apply 'command (append '("pline") coords '("c")))
(setq currobj (ssadd (entlast) currobj))
(setq coords (list 
(list 2880.5625 820.48) 
(list 2954.585 821.13) 
(list 2954.585 821.307) 
(list 2880.5625 820.557)))
(apply 'command (append '("pline") coords '("c")))
(setq currobj (ssadd (entlast) currobj))
(setq coords (list 
(list 2879.4375 820.557) 
(list 2805.415 821.307) 
(list 2805.415 821.13) 
(list 2879.4375 820.48)))
(apply 'command (append '("pline") coords '("c")))
(setq currobj (ssadd (entlast) currobj))
(setq coords (list 
(list 2879.4375 820.337) 
(list 2805.415 820.987) 
(list 2805.415 820.81) 
(list 2879.4375 820.26)))
(apply 'command (append '("pline") coords '("c")))
(setq currobj (ssadd (entlast) currobj))
(setq coords (list 
(list 2879.4375 820.117) 
(list 2805.415 820.667) 
(list 2805.415 820.49) 
(list 2879.4375 820.04)))
(apply 'command (append '("pline") coords '("c")))
(setq currobj (ssadd (entlast) currobj))
(setq coords (list 
(list 2879.4375 819.897) 
(list 2805.415 820.347) 
(list 2805.415 820.17) 
(list 2879.4375 819.82)))
(apply 'command (append '("pline") coords '("c")))
(setq currobj (ssadd (entlast) currobj))
(setq coords (list 
(list 2879.4375 819.677) 
(list 2805.415 820.027) 
(list 2805.415 819.85) 
(list 2879.4375 819.6)))
(apply 'command (append '("pline") coords '("c")))
(setq currobj (ssadd (entlast) currobj))
(setq coords (list 
(list 2879.4375 819.457) 
(list 2805.415 819.707) 
(list 2805.415 819.53) 
(list 2879.4375 819.38)))
(apply 'command (append '("pline") coords '("c")))
(setq currobj (ssadd (entlast) currobj))
(setq coords (list 
(list 2879.4375 819.237) 
(list 2805.415 819.387) 
(list 2805.415 819.21) 
(list 2879.4375 819.16)))
(apply 'command (append '("pline") coords '("c")))
(setq currobj (ssadd (entlast) currobj))
(setq coords (list 
(list 2879.4375 819.017) 
(list 2805.415 819.067) 
(list 2805.415 818.89) 
(list 2879.4375 818.94)))
(apply 'command (append '("pline") coords '("c")))
(setq currobj (ssadd (entlast) currobj))
(setq coords (list 
(list 2879.4375 818.797) 
(list 2805.415 818.747) 
(list 2805.415 818.57) 
(list 2879.4375 818.72)))
(apply 'command (append '("pline") coords '("c")))
(setq currobj (ssadd (entlast) currobj))
(setq coords (list 
(list 2879.4375 818.577) 
(list 2805.415 818.427) 
(list 2805.415 818.25) 
(list 2879.4375 818.5)))
(apply 'command (append '("pline") coords '("c")))
(setq currobj (ssadd (entlast) currobj))
(setq coords (list 
(list 2879.4375 818.357) 
(list 2805.415 818.107) 
(list 2805.415 817.93) 
(list 2879.4375 818.28)))
(apply 'command (append '("pline") coords '("c")))
(setq currobj (ssadd (entlast) currobj))
(setq coords (list 
(list 2879.4375 818.137) 
(list 2805.415 817.787) 
(list 2805.415 817.61) 
(list 2879.4375 818.06)))
(apply 'command (append '("pline") coords '("c")))
(setq currobj (ssadd (entlast) currobj))
(setq coords (list 
(list 2879.4375 817.917) 
(list 2805.415 817.467) 
(list 2805.415 817.29) 
(list 2879.4375 817.84)))
(apply 'command (append '("pline") coords '("c")))
(setq currobj (ssadd (entlast) currobj))
(setq coords (list 
(list 2879.4375 817.697) 
(list 2805.415 817.147) 
(list 2805.415 816.97) 
(list 2879.4375 817.62)))
(apply 'command (append '("pline") coords '("c")))
(setq currobj (ssadd (entlast) currobj))
(setq coords (list 
(list 2879.4375 817.477) 
(list 2805.415 816.827) 
(list 2805.415 816.65) 
(list 2879.4375 817.4)))
(apply 'command (append '("pline") coords '("c")))
(setq currobj (ssadd (entlast) currobj))
(command "_layer" "set" "nitride" "")
(command "_layer" "set" "text" "")
(command "_circle" "2879.0625,806.257" "0.075")
(command "_circle" "2879.0625,806.557" "0.075")
(command "_circle" "2879.0625,806.857" "0.075")
(command "_circle" "2879.0625,807.157" "0.075")
(command "_circle" "2879.0625,807.457" "0.075")
(command "_circle" "2878.7625,806.257" "0.075")
(command "_circle" "2878.7625,806.557" "0.075")
(command "_circle" "2878.7625,806.857" "0.075")
(command "_circle" "2878.7625,807.157" "0.075")
(command "_circle" "2878.7625,807.457" "0.075")
(command "_circle" "2878.4625,806.257" "0.075")
(command "_circle" "2878.4625,806.557" "0.075")
(command "_circle" "2878.4625,806.857" "0.075")
(command "_circle" "2878.4625,807.157" "0.075")
(command "_circle" "2878.4625,807.457" "0.075")
(command "_circle" "2878.1625,806.257" "0.075")
(command "_circle" "2878.1625,806.557" "0.075")
(command "_circle" "2878.1625,806.857" "0.075")
(command "_circle" "2878.1625,807.157" "0.075")
(command "_circle" "2878.1625,807.457" "0.075")
(command "_circle" "2877.8625,806.257" "0.075")
(command "_circle" "2877.8625,806.557" "0.075")
(command "_circle" "2877.8625,806.857" "0.075")
(command "_circle" "2877.8625,807.157" "0.075")
(command "_circle" "2877.8625,807.457" "0.075")
(command "_layer" "set" "nitride" "")
(setq coords (list 
(list 2880.2625 831.7) 
(list 2880.2625 836.7) 
(list 2879.7375 836.7) 
(list 2879.7375 831.7)))
(apply 'command (append '("pline") coords '("c")))
(setq currobj (ssadd (entlast) currobj))
(command "_layer" "set" "prebias" "")
(command "_rectangle" "2879.7375,831.7" "2880.2625,836.7")
(setq currobj (ssadd (entlast) currobj))
(command "_layer" "set" "nitride" "")
(setq cooledsinglenanobeam9 currobj)
(setq currobj nil)
(setq currobj (ssadd))
; DRAWING PHOTONIC CRYSTAL
(command "_layer" "set" "negYjunc" "")
(setq coords (list 
(list 2880.135 866.7) 
(list 2880 851.7) 
(list 2880 866.7)))
(apply 'command (append '("pline") coords '("c")))
(setq currobj (ssadd (entlast) currobj))
(setq coords (list 
(list 2880.2625 836.7) 
(list 2880.415 866.7) 
(list 2881.13 866.7) 
(list 2881.13 836.7)))
(apply 'command (append '("pline") coords '("c")))
(setq currobj (ssadd (entlast) currobj))
(setq coords (list 
(list 2879.865 866.7) 
(list 2880 851.7) 
(list 2880 866.7)))
(apply 'command (append '("pline") coords '("c")))
(setq currobj (ssadd (entlast) currobj))
(setq coords (list 
(list 2879.7375 836.7) 
(list 2879.585 866.7) 
(list 2878.87 866.7) 
(list 2878.87 836.7)))
(apply 'command (append '("pline") coords '("c")))
(setq currobj (ssadd (entlast) currobj))
(command "_layer" "set" "nitride" "")
(setq yjunction9 currobj)
(setq currobj nil)
(setq currobj (ssadd))
(setq tap9 nil)
(setq tap9 (ssadd))
(command "_layer" "set" "phc" "")
(setq coords (list 
(list 2880 866.7) 
(list 2880.135 866.7) 
(list 2880.135 866.7103) 
(list 2880.135 866.7206) 
(list 2880.135 866.7308) 
(list 2880.135 866.7411) 
(list 2880.135 866.7514) 
(list 2880.135 866.7617) 
(list 2880.135 866.7719) 
(list 2880.135 866.7822) 
(list 2880.135 866.7925) 
(list 2880.135 866.8028) 
(list 2880.135 866.8131) 
(list 2880.135 866.8233) 
(list 2880.135 866.8336) 
(list 2880.135 866.8439) 
(list 2880.135 866.8542) 
(list 2880.135 866.8644) 
(list 2880.135 866.8747) 
(list 2880.135 866.885) 
(list 2880.135 866.8953) 
(list 2880.135 866.9056) 
(list 2880.135 866.9158) 
(list 2880.135 866.9261) 
(list 2880.135 866.9364) 
(list 2880.135 866.9467) 
(list 2880.135 866.9569) 
(list 2880.135 866.9672) 
(list 2880.135 866.9775) 
(list 2880.135 866.9878) 
(list 2880.135 866.9981) 
(list 2880.135 867.0083) 
(list 2880.135 867.0186) 
(list 2880.135 867.0289) 
(list 2880.135 867.0392) 
(list 2880.135 867.0494) 
(list 2880.135 867.0597) 
(list 2880.135 867.07) 
(list 2880 867.07)))
(apply 'command (append '("pline") coords '("c")))
(setq tap9 (ssadd (entlast) tap9))
(command "_mirror" (entlast) "" "2880,900" "2880,901" "No")
(setq tap9 (ssadd (entlast) tap9))
(setq coords (list 
(list 2880.425 866.7) 
(list 2880.415 866.7) 
(list 2880.4153 866.7103) 
(list 2880.4155 866.7206) 
(list 2880.4157 866.7308) 
(list 2880.4159 866.7411) 
(list 2880.4159 866.7514) 
(list 2880.4159 866.7617) 
(list 2880.4158 866.7719) 
(list 2880.4156 866.7822) 
(list 2880.4153 866.7925) 
(list 2880.4149 866.8028) 
(list 2880.4144 866.8131) 
(list 2880.4139 866.8233) 
(list 2880.4133 866.8336) 
(list 2880.4128 866.8439) 
(list 2880.4122 866.8542) 
(list 2880.4117 866.8644) 
(list 2880.4113 866.8747) 
(list 2880.4111 866.885) 
(list 2880.4109 866.8953) 
(list 2880.4109 866.9056) 
(list 2880.4111 866.9158) 
(list 2880.4115 866.9261) 
(list 2880.412 866.9364) 
(list 2880.4127 866.9467) 
(list 2880.4136 866.9569) 
(list 2880.4147 866.9672) 
(list 2880.4158 866.9775) 
(list 2880.417 866.9878) 
(list 2880.4183 866.9981) 
(list 2880.4196 867.0083) 
(list 2880.4209 867.0186) 
(list 2880.422 867.0289) 
(list 2880.4231 867.0392) 
(list 2880.4239 867.0494) 
(list 2880.4246 867.0597) 
(list 2880.425 867.07) 
(list 2880.425 867.07)))
(apply 'command (append '("pline") coords '("c")))
(setq tap9 (ssadd (entlast) tap9))
(command "_mirror" (entlast) "" "2880,900" "2880,901" "No")
(setq tap9 (ssadd (entlast) tap9))
(setq coords (list 
(list 2881.13 866.7) 
(list 2880.425 866.7) 
(list 2880.425 866.7103) 
(list 2880.425 866.7206) 
(list 2880.425 866.7308) 
(list 2880.425 866.7411) 
(list 2880.425 866.7514) 
(list 2880.425 866.7617) 
(list 2880.425 866.7719) 
(list 2880.425 866.7822) 
(list 2880.425 866.7925) 
(list 2880.425 866.8028) 
(list 2880.425 866.8131) 
(list 2880.425 866.8233) 
(list 2880.425 866.8336) 
(list 2880.425 866.8439) 
(list 2880.425 866.8542) 
(list 2880.425 866.8644) 
(list 2880.425 866.8747) 
(list 2880.425 866.885) 
(list 2880.425 866.8953) 
(list 2880.425 866.9056) 
(list 2880.425 866.9158) 
(list 2880.425 866.9261) 
(list 2880.425 866.9364) 
(list 2880.425 866.9467) 
(list 2880.425 866.9569) 
(list 2880.425 866.9672) 
(list 2880.425 866.9775) 
(list 2880.425 866.9878) 
(list 2880.425 866.9981) 
(list 2880.425 867.0083) 
(list 2880.425 867.0186) 
(list 2880.425 867.0289) 
(list 2880.425 867.0392) 
(list 2880.425 867.0494) 
(list 2880.425 867.0597) 
(list 2880.425 867.07) 
(list 2881.13 867.07)))
(apply 'command (append '("pline") coords '("c")))
(setq tap9 (ssadd (entlast) tap9))
(command "_mirror" (entlast) "" "2880,900" "2880,901" "No")
(setq tap9 (ssadd (entlast) tap9))
(setq coords (list 
(list 2880 867.07) 
(list 2880.135 867.07) 
(list 2880.135 867.0803) 
(list 2880.135 867.0906) 
(list 2880.135 867.1008) 
(list 2880.135 867.1111) 
(list 2880.135 867.1214) 
(list 2880.135 867.1317) 
(list 2880.135 867.1419) 
(list 2880.135 867.1522) 
(list 2880.135 867.1625) 
(list 2880.135 867.1728) 
(list 2880.135 867.1831) 
(list 2880.135 867.1933) 
(list 2880.135 867.2036) 
(list 2880.135 867.2139) 
(list 2880.135 867.2242) 
(list 2880.135 867.2344) 
(list 2880.135 867.2447) 
(list 2880.135 867.255) 
(list 2880.135 867.2653) 
(list 2880.135 867.2756) 
(list 2880.135 867.2858) 
(list 2880.135 867.2961) 
(list 2880.135 867.3064) 
(list 2880.135 867.3167) 
(list 2880.135 867.3269) 
(list 2880.135 867.3372) 
(list 2880.135 867.3475) 
(list 2880.135 867.3578) 
(list 2880.135 867.3681) 
(list 2880.135 867.3783) 
(list 2880.135 867.3886) 
(list 2880.135 867.3989) 
(list 2880.135 867.4092) 
(list 2880.135 867.4194) 
(list 2880.135 867.4297) 
(list 2880.135 867.44) 
(list 2880 867.44)))
(apply 'command (append '("pline") coords '("c")))
(setq tap9 (ssadd (entlast) tap9))
(command "_mirror" (entlast) "" "2880,900" "2880,901" "No")
(setq tap9 (ssadd (entlast) tap9))
(setq coords (list 
(list 2880.435 867.07) 
(list 2880.425 867.07) 
(list 2880.4251 867.0803) 
(list 2880.425 867.0906) 
(list 2880.4245 867.1008) 
(list 2880.4238 867.1111) 
(list 2880.4228 867.1214) 
(list 2880.4215 867.1317) 
(list 2880.4199 867.1419) 
(list 2880.4182 867.1522) 
(list 2880.4163 867.1625) 
(list 2880.4144 867.1728) 
(list 2880.4124 867.1831) 
(list 2880.4105 867.1933) 
(list 2880.4086 867.2036) 
(list 2880.407 867.2139) 
(list 2880.4056 867.2242) 
(list 2880.4044 867.2344) 
(list 2880.4036 867.2447) 
(list 2880.4032 867.255) 
(list 2880.4032 867.2653) 
(list 2880.4036 867.2756) 
(list 2880.4044 867.2858) 
(list 2880.4057 867.2961) 
(list 2880.4073 867.3064) 
(list 2880.4093 867.3167) 
(list 2880.4116 867.3269) 
(list 2880.4142 867.3372) 
(list 2880.4169 867.3475) 
(list 2880.4197 867.3578) 
(list 2880.4224 867.3681) 
(list 2880.4251 867.3783) 
(list 2880.4277 867.3886) 
(list 2880.4299 867.3989) 
(list 2880.4319 867.4092) 
(list 2880.4334 867.4194) 
(list 2880.4345 867.4297) 
(list 2880.435 867.44) 
(list 2880.435 867.44)))
(apply 'command (append '("pline") coords '("c")))
(setq tap9 (ssadd (entlast) tap9))
(command "_mirror" (entlast) "" "2880,900" "2880,901" "No")
(setq tap9 (ssadd (entlast) tap9))
(setq coords (list 
(list 2881.13 867.07) 
(list 2880.435 867.07) 
(list 2880.435 867.0803) 
(list 2880.435 867.0906) 
(list 2880.435 867.1008) 
(list 2880.435 867.1111) 
(list 2880.435 867.1214) 
(list 2880.435 867.1317) 
(list 2880.435 867.1419) 
(list 2880.435 867.1522) 
(list 2880.435 867.1625) 
(list 2880.435 867.1728) 
(list 2880.435 867.1831) 
(list 2880.435 867.1933) 
(list 2880.435 867.2036) 
(list 2880.435 867.2139) 
(list 2880.435 867.2242) 
(list 2880.435 867.2344) 
(list 2880.435 867.2447) 
(list 2880.435 867.255) 
(list 2880.435 867.2653) 
(list 2880.435 867.2756) 
(list 2880.435 867.2858) 
(list 2880.435 867.2961) 
(list 2880.435 867.3064) 
(list 2880.435 867.3167) 
(list 2880.435 867.3269) 
(list 2880.435 867.3372) 
(list 2880.435 867.3475) 
(list 2880.435 867.3578) 
(list 2880.435 867.3681) 
(list 2880.435 867.3783) 
(list 2880.435 867.3886) 
(list 2880.435 867.3989) 
(list 2880.435 867.4092) 
(list 2880.435 867.4194) 
(list 2880.435 867.4297) 
(list 2880.435 867.44) 
(list 2881.13 867.44)))
(apply 'command (append '("pline") coords '("c")))
(setq tap9 (ssadd (entlast) tap9))
(command "_mirror" (entlast) "" "2880,900" "2880,901" "No")
(setq tap9 (ssadd (entlast) tap9))
(setq coords (list 
(list 2880 867.44) 
(list 2880.135 867.44) 
(list 2880.135 867.4503) 
(list 2880.135 867.4606) 
(list 2880.135 867.4708) 
(list 2880.135 867.4811) 
(list 2880.135 867.4914) 
(list 2880.135 867.5017) 
(list 2880.135 867.5119) 
(list 2880.135 867.5222) 
(list 2880.135 867.5325) 
(list 2880.135 867.5428) 
(list 2880.135 867.5531) 
(list 2880.135 867.5633) 
(list 2880.135 867.5736) 
(list 2880.135 867.5839) 
(list 2880.135 867.5942) 
(list 2880.135 867.6044) 
(list 2880.135 867.6147) 
(list 2880.135 867.625) 
(list 2880.135 867.6353) 
(list 2880.135 867.6456) 
(list 2880.135 867.6558) 
(list 2880.135 867.6661) 
(list 2880.135 867.6764) 
(list 2880.135 867.6867) 
(list 2880.135 867.6969) 
(list 2880.135 867.7072) 
(list 2880.135 867.7175) 
(list 2880.135 867.7278) 
(list 2880.135 867.7381) 
(list 2880.135 867.7483) 
(list 2880.135 867.7586) 
(list 2880.135 867.7689) 
(list 2880.135 867.7792) 
(list 2880.135 867.7894) 
(list 2880.135 867.7997) 
(list 2880.135 867.81) 
(list 2880 867.81)))
(apply 'command (append '("pline") coords '("c")))
(setq tap9 (ssadd (entlast) tap9))
(command "_mirror" (entlast) "" "2880,900" "2880,901" "No")
(setq tap9 (ssadd (entlast) tap9))
(setq coords (list 
(list 2880.445 867.44) 
(list 2880.435 867.44) 
(list 2880.435 867.4503) 
(list 2880.4344 867.4606) 
(list 2880.4333 867.4708) 
(list 2880.4317 867.4811) 
(list 2880.4296 867.4914) 
(list 2880.427 867.5017) 
(list 2880.424 867.5119) 
(list 2880.4208 867.5222) 
(list 2880.4174 867.5325) 
(list 2880.4139 867.5428) 
(list 2880.4104 867.5531) 
(list 2880.4071 867.5633) 
(list 2880.404 867.5736) 
(list 2880.4012 867.5839) 
(list 2880.3989 867.5942) 
(list 2880.3971 867.6044) 
(list 2880.3959 867.6147) 
(list 2880.3953 867.625) 
(list 2880.3955 867.6353) 
(list 2880.3963 867.6456) 
(list 2880.3978 867.6558) 
(list 2880.3999 867.6661) 
(list 2880.4027 867.6764) 
(list 2880.4059 867.6867) 
(list 2880.4096 867.6969) 
(list 2880.4137 867.7072) 
(list 2880.4179 867.7175) 
(list 2880.4223 867.7278) 
(list 2880.4266 867.7381) 
(list 2880.4307 867.7483) 
(list 2880.4345 867.7586) 
(list 2880.4379 867.7689) 
(list 2880.4407 867.7792) 
(list 2880.4429 867.7894) 
(list 2880.4443 867.7997) 
(list 2880.445 867.81) 
(list 2880.445 867.81)))
(apply 'command (append '("pline") coords '("c")))
(setq tap9 (ssadd (entlast) tap9))
(command "_mirror" (entlast) "" "2880,900" "2880,901" "No")
(setq tap9 (ssadd (entlast) tap9))
(setq coords (list 
(list 2881.13 867.44) 
(list 2880.445 867.44) 
(list 2880.445 867.4503) 
(list 2880.445 867.4606) 
(list 2880.445 867.4708) 
(list 2880.445 867.4811) 
(list 2880.445 867.4914) 
(list 2880.445 867.5017) 
(list 2880.445 867.5119) 
(list 2880.445 867.5222) 
(list 2880.445 867.5325) 
(list 2880.445 867.5428) 
(list 2880.445 867.5531) 
(list 2880.445 867.5633) 
(list 2880.445 867.5736) 
(list 2880.445 867.5839) 
(list 2880.445 867.5942) 
(list 2880.445 867.6044) 
(list 2880.445 867.6147) 
(list 2880.445 867.625) 
(list 2880.445 867.6353) 
(list 2880.445 867.6456) 
(list 2880.445 867.6558) 
(list 2880.445 867.6661) 
(list 2880.445 867.6764) 
(list 2880.445 867.6867) 
(list 2880.445 867.6969) 
(list 2880.445 867.7072) 
(list 2880.445 867.7175) 
(list 2880.445 867.7278) 
(list 2880.445 867.7381) 
(list 2880.445 867.7483) 
(list 2880.445 867.7586) 
(list 2880.445 867.7689) 
(list 2880.445 867.7792) 
(list 2880.445 867.7894) 
(list 2880.445 867.7997) 
(list 2880.445 867.81) 
(list 2881.13 867.81)))
(apply 'command (append '("pline") coords '("c")))
(setq tap9 (ssadd (entlast) tap9))
(command "_mirror" (entlast) "" "2880,900" "2880,901" "No")
(setq tap9 (ssadd (entlast) tap9))
(setq coords (list 
(list 2880 867.81) 
(list 2880.135 867.81) 
(list 2880.135 867.8203) 
(list 2880.135 867.8306) 
(list 2880.135 867.8408) 
(list 2880.135 867.8511) 
(list 2880.135 867.8614) 
(list 2880.135 867.8717) 
(list 2880.135 867.8819) 
(list 2880.135 867.8922) 
(list 2880.135 867.9025) 
(list 2880.135 867.9128) 
(list 2880.135 867.9231) 
(list 2880.135 867.9333) 
(list 2880.135 867.9436) 
(list 2880.135 867.9539) 
(list 2880.135 867.9642) 
(list 2880.135 867.9744) 
(list 2880.135 867.9847) 
(list 2880.135 867.995) 
(list 2880.135 868.0053) 
(list 2880.135 868.0156) 
(list 2880.135 868.0258) 
(list 2880.135 868.0361) 
(list 2880.135 868.0464) 
(list 2880.135 868.0567) 
(list 2880.135 868.0669) 
(list 2880.135 868.0772) 
(list 2880.135 868.0875) 
(list 2880.135 868.0978) 
(list 2880.135 868.1081) 
(list 2880.135 868.1183) 
(list 2880.135 868.1286) 
(list 2880.135 868.1389) 
(list 2880.135 868.1492) 
(list 2880.135 868.1594) 
(list 2880.135 868.1697) 
(list 2880.135 868.18) 
(list 2880 868.18)))
(apply 'command (append '("pline") coords '("c")))
(setq tap9 (ssadd (entlast) tap9))
(command "_mirror" (entlast) "" "2880,900" "2880,901" "No")
(setq tap9 (ssadd (entlast) tap9))
(setq coords (list 
(list 2880.455 867.81) 
(list 2880.445 867.81) 
(list 2880.4449 867.8203) 
(list 2880.4439 867.8306) 
(list 2880.4421 867.8408) 
(list 2880.4396 867.8511) 
(list 2880.4364 867.8614) 
(list 2880.4325 867.8717) 
(list 2880.4282 867.8819) 
(list 2880.4234 867.8922) 
(list 2880.4185 867.9025) 
(list 2880.4134 867.9128) 
(list 2880.4084 867.9231) 
(list 2880.4037 867.9333) 
(list 2880.3993 867.9436) 
(list 2880.3954 867.9539) 
(list 2880.3922 867.9642) 
(list 2880.3898 867.9744) 
(list 2880.3882 867.9847) 
(list 2880.3875 867.995) 
(list 2880.3877 868.0053) 
(list 2880.3889 868.0156) 
(list 2880.3911 868.0258) 
(list 2880.3941 868.0361) 
(list 2880.398 868.0464) 
(list 2880.4025 868.0567) 
(list 2880.4077 868.0669) 
(list 2880.4132 868.0772) 
(list 2880.419 868.0875) 
(list 2880.4249 868.0978) 
(list 2880.4307 868.1081) 
(list 2880.4362 868.1183) 
(list 2880.4413 868.1286) 
(list 2880.4458 868.1389) 
(list 2880.4495 868.1492) 
(list 2880.4523 868.1594) 
(list 2880.4542 868.1697) 
(list 2880.455 868.18) 
(list 2880.455 868.18)))
(apply 'command (append '("pline") coords '("c")))
(setq tap9 (ssadd (entlast) tap9))
(command "_mirror" (entlast) "" "2880,900" "2880,901" "No")
(setq tap9 (ssadd (entlast) tap9))
(setq coords (list 
(list 2881.13 867.81) 
(list 2880.455 867.81) 
(list 2880.455 867.8203) 
(list 2880.455 867.8306) 
(list 2880.455 867.8408) 
(list 2880.455 867.8511) 
(list 2880.455 867.8614) 
(list 2880.455 867.8717) 
(list 2880.455 867.8819) 
(list 2880.455 867.8922) 
(list 2880.455 867.9025) 
(list 2880.455 867.9128) 
(list 2880.455 867.9231) 
(list 2880.455 867.9333) 
(list 2880.455 867.9436) 
(list 2880.455 867.9539) 
(list 2880.455 867.9642) 
(list 2880.455 867.9744) 
(list 2880.455 867.9847) 
(list 2880.455 867.995) 
(list 2880.455 868.0053) 
(list 2880.455 868.0156) 
(list 2880.455 868.0258) 
(list 2880.455 868.0361) 
(list 2880.455 868.0464) 
(list 2880.455 868.0567) 
(list 2880.455 868.0669) 
(list 2880.455 868.0772) 
(list 2880.455 868.0875) 
(list 2880.455 868.0978) 
(list 2880.455 868.1081) 
(list 2880.455 868.1183) 
(list 2880.455 868.1286) 
(list 2880.455 868.1389) 
(list 2880.455 868.1492) 
(list 2880.455 868.1594) 
(list 2880.455 868.1697) 
(list 2880.455 868.18) 
(list 2881.13 868.18)))
(apply 'command (append '("pline") coords '("c")))
(setq tap9 (ssadd (entlast) tap9))
(command "_mirror" (entlast) "" "2880,900" "2880,901" "No")
(setq tap9 (ssadd (entlast) tap9))
(setq coords (list 
(list 2880 868.18) 
(list 2880.135 868.18) 
(list 2880.135 868.1903) 
(list 2880.135 868.2006) 
(list 2880.135 868.2108) 
(list 2880.135 868.2211) 
(list 2880.135 868.2314) 
(list 2880.135 868.2417) 
(list 2880.135 868.2519) 
(list 2880.135 868.2622) 
(list 2880.135 868.2725) 
(list 2880.135 868.2828) 
(list 2880.135 868.2931) 
(list 2880.135 868.3033) 
(list 2880.135 868.3136) 
(list 2880.135 868.3239) 
(list 2880.135 868.3342) 
(list 2880.135 868.3444) 
(list 2880.135 868.3547) 
(list 2880.135 868.365) 
(list 2880.135 868.3753) 
(list 2880.135 868.3856) 
(list 2880.135 868.3958) 
(list 2880.135 868.4061) 
(list 2880.135 868.4164) 
(list 2880.135 868.4267) 
(list 2880.135 868.4369) 
(list 2880.135 868.4472) 
(list 2880.135 868.4575) 
(list 2880.135 868.4678) 
(list 2880.135 868.4781) 
(list 2880.135 868.4883) 
(list 2880.135 868.4986) 
(list 2880.135 868.5089) 
(list 2880.135 868.5192) 
(list 2880.135 868.5294) 
(list 2880.135 868.5397) 
(list 2880.135 868.55) 
(list 2880 868.55)))
(apply 'command (append '("pline") coords '("c")))
(setq tap9 (ssadd (entlast) tap9))
(command "_mirror" (entlast) "" "2880,900" "2880,901" "No")
(setq tap9 (ssadd (entlast) tap9))
(setq coords (list 
(list 2880.465 868.18) 
(list 2880.455 868.18) 
(list 2880.4547 868.1903) 
(list 2880.4534 868.2006) 
(list 2880.4509 868.2108) 
(list 2880.4475 868.2211) 
(list 2880.4432 868.2314) 
(list 2880.4381 868.2417) 
(list 2880.4323 868.2519) 
(list 2880.4261 868.2622) 
(list 2880.4195 868.2725) 
(list 2880.4129 868.2828) 
(list 2880.4064 868.2931) 
(list 2880.4003 868.3033) 
(list 2880.3946 868.3136) 
(list 2880.3896 868.3239) 
(list 2880.3855 868.3342) 
(list 2880.3824 868.3444) 
(list 2880.3804 868.3547) 
(list 2880.3796 868.365) 
(list 2880.38 868.3753) 
(list 2880.3816 868.3856) 
(list 2880.3844 868.3958) 
(list 2880.3884 868.4061) 
(list 2880.3933 868.4164) 
(list 2880.3991 868.4267) 
(list 2880.4057 868.4369) 
(list 2880.4127 868.4472) 
(list 2880.4201 868.4575) 
(list 2880.4275 868.4678) 
(list 2880.4348 868.4781) 
(list 2880.4417 868.4883) 
(list 2880.4481 868.4986) 
(list 2880.4537 868.5089) 
(list 2880.4583 868.5192) 
(list 2880.4618 868.5294) 
(list 2880.464 868.5397) 
(list 2880.465 868.55) 
(list 2880.465 868.55)))
(apply 'command (append '("pline") coords '("c")))
(setq tap9 (ssadd (entlast) tap9))
(command "_mirror" (entlast) "" "2880,900" "2880,901" "No")
(setq tap9 (ssadd (entlast) tap9))
(setq coords (list 
(list 2881.13 868.18) 
(list 2880.465 868.18) 
(list 2880.465 868.1903) 
(list 2880.465 868.2006) 
(list 2880.465 868.2108) 
(list 2880.465 868.2211) 
(list 2880.465 868.2314) 
(list 2880.465 868.2417) 
(list 2880.465 868.2519) 
(list 2880.465 868.2622) 
(list 2880.465 868.2725) 
(list 2880.465 868.2828) 
(list 2880.465 868.2931) 
(list 2880.465 868.3033) 
(list 2880.465 868.3136) 
(list 2880.465 868.3239) 
(list 2880.465 868.3342) 
(list 2880.465 868.3444) 
(list 2880.465 868.3547) 
(list 2880.465 868.365) 
(list 2880.465 868.3753) 
(list 2880.465 868.3856) 
(list 2880.465 868.3958) 
(list 2880.465 868.4061) 
(list 2880.465 868.4164) 
(list 2880.465 868.4267) 
(list 2880.465 868.4369) 
(list 2880.465 868.4472) 
(list 2880.465 868.4575) 
(list 2880.465 868.4678) 
(list 2880.465 868.4781) 
(list 2880.465 868.4883) 
(list 2880.465 868.4986) 
(list 2880.465 868.5089) 
(list 2880.465 868.5192) 
(list 2880.465 868.5294) 
(list 2880.465 868.5397) 
(list 2880.465 868.55) 
(list 2881.13 868.55)))
(apply 'command (append '("pline") coords '("c")))
(setq tap9 (ssadd (entlast) tap9))
(command "_mirror" (entlast) "" "2880,900" "2880,901" "No")
(setq tap9 (ssadd (entlast) tap9))
(setq coords (list 
(list 2880 868.55) 
(list 2880.135 868.55) 
(list 2880.135 868.5603) 
(list 2880.135 868.5706) 
(list 2880.135 868.5808) 
(list 2880.135 868.5911) 
(list 2880.135 868.6014) 
(list 2880.135 868.6117) 
(list 2880.135 868.6219) 
(list 2880.135 868.6322) 
(list 2880.135 868.6425) 
(list 2880.135 868.6528) 
(list 2880.135 868.6631) 
(list 2880.135 868.6733) 
(list 2880.135 868.6836) 
(list 2880.135 868.6939) 
(list 2880.135 868.7042) 
(list 2880.135 868.7144) 
(list 2880.135 868.7247) 
(list 2880.135 868.735) 
(list 2880.135 868.7453) 
(list 2880.135 868.7556) 
(list 2880.135 868.7658) 
(list 2880.135 868.7761) 
(list 2880.135 868.7864) 
(list 2880.135 868.7967) 
(list 2880.135 868.8069) 
(list 2880.135 868.8172) 
(list 2880.135 868.8275) 
(list 2880.135 868.8378) 
(list 2880.135 868.8481) 
(list 2880.135 868.8583) 
(list 2880.135 868.8686) 
(list 2880.135 868.8789) 
(list 2880.135 868.8892) 
(list 2880.135 868.8994) 
(list 2880.135 868.9097) 
(list 2880.135 868.92) 
(list 2880 868.92)))
(apply 'command (append '("pline") coords '("c")))
(setq tap9 (ssadd (entlast) tap9))
(command "_mirror" (entlast) "" "2880,900" "2880,901" "No")
(setq tap9 (ssadd (entlast) tap9))
(setq coords (list 
(list 2880.475 868.55) 
(list 2880.465 868.55) 
(list 2880.4646 868.5603) 
(list 2880.4628 868.5706) 
(list 2880.4597 868.5808) 
(list 2880.4554 868.5911) 
(list 2880.45 868.6014) 
(list 2880.4436 868.6117) 
(list 2880.4364 868.6219) 
(list 2880.4287 868.6322) 
(list 2880.4206 868.6425) 
(list 2880.4124 868.6528) 
(list 2880.4044 868.6631) 
(list 2880.3969 868.6733) 
(list 2880.3899 868.6836) 
(list 2880.3839 868.6939) 
(list 2880.3789 868.7042) 
(list 2880.3751 868.7144) 
(list 2880.3727 868.7247) 
(list 2880.3717 868.735) 
(list 2880.3723 868.7453) 
(list 2880.3743 868.7556) 
(list 2880.3778 868.7658) 
(list 2880.3826 868.7761) 
(list 2880.3886 868.7864) 
(list 2880.3957 868.7967) 
(list 2880.4037 868.8069) 
(list 2880.4122 868.8172) 
(list 2880.4211 868.8275) 
(list 2880.4301 868.8378) 
(list 2880.4389 868.8481) 
(list 2880.4473 868.8583) 
(list 2880.4549 868.8686) 
(list 2880.4616 868.8789) 
(list 2880.4671 868.8892) 
(list 2880.4712 868.8994) 
(list 2880.4739 868.9097) 
(list 2880.475 868.92) 
(list 2880.475 868.92)))
(apply 'command (append '("pline") coords '("c")))
(setq tap9 (ssadd (entlast) tap9))
(command "_mirror" (entlast) "" "2880,900" "2880,901" "No")
(setq tap9 (ssadd (entlast) tap9))
(setq coords (list 
(list 2881.13 868.55) 
(list 2880.475 868.55) 
(list 2880.475 868.5603) 
(list 2880.475 868.5706) 
(list 2880.475 868.5808) 
(list 2880.475 868.5911) 
(list 2880.475 868.6014) 
(list 2880.475 868.6117) 
(list 2880.475 868.6219) 
(list 2880.475 868.6322) 
(list 2880.475 868.6425) 
(list 2880.475 868.6528) 
(list 2880.475 868.6631) 
(list 2880.475 868.6733) 
(list 2880.475 868.6836) 
(list 2880.475 868.6939) 
(list 2880.475 868.7042) 
(list 2880.475 868.7144) 
(list 2880.475 868.7247) 
(list 2880.475 868.735) 
(list 2880.475 868.7453) 
(list 2880.475 868.7556) 
(list 2880.475 868.7658) 
(list 2880.475 868.7761) 
(list 2880.475 868.7864) 
(list 2880.475 868.7967) 
(list 2880.475 868.8069) 
(list 2880.475 868.8172) 
(list 2880.475 868.8275) 
(list 2880.475 868.8378) 
(list 2880.475 868.8481) 
(list 2880.475 868.8583) 
(list 2880.475 868.8686) 
(list 2880.475 868.8789) 
(list 2880.475 868.8892) 
(list 2880.475 868.8994) 
(list 2880.475 868.9097) 
(list 2880.475 868.92) 
(list 2881.13 868.92)))
(apply 'command (append '("pline") coords '("c")))
(setq tap9 (ssadd (entlast) tap9))
(command "_mirror" (entlast) "" "2880,900" "2880,901" "No")
(setq tap9 (ssadd (entlast) tap9))
(setq coords (list 
(list 2880 868.92) 
(list 2880.135 868.92) 
(list 2880.135 868.9303) 
(list 2880.135 868.9406) 
(list 2880.135 868.9508) 
(list 2880.135 868.9611) 
(list 2880.135 868.9714) 
(list 2880.135 868.9817) 
(list 2880.135 868.9919) 
(list 2880.135 869.0022) 
(list 2880.135 869.0125) 
(list 2880.135 869.0228) 
(list 2880.135 869.0331) 
(list 2880.135 869.0433) 
(list 2880.135 869.0536) 
(list 2880.135 869.0639) 
(list 2880.135 869.0742) 
(list 2880.135 869.0844) 
(list 2880.135 869.0947) 
(list 2880.135 869.105) 
(list 2880.135 869.1153) 
(list 2880.135 869.1256) 
(list 2880.135 869.1358) 
(list 2880.135 869.1461) 
(list 2880.135 869.1564) 
(list 2880.135 869.1667) 
(list 2880.135 869.1769) 
(list 2880.135 869.1872) 
(list 2880.135 869.1975) 
(list 2880.135 869.2078) 
(list 2880.135 869.2181) 
(list 2880.135 869.2283) 
(list 2880.135 869.2386) 
(list 2880.135 869.2489) 
(list 2880.135 869.2592) 
(list 2880.135 869.2694) 
(list 2880.135 869.2797) 
(list 2880.135 869.29) 
(list 2880 869.29)))
(apply 'command (append '("pline") coords '("c")))
(setq tap9 (ssadd (entlast) tap9))
(command "_mirror" (entlast) "" "2880,900" "2880,901" "No")
(setq tap9 (ssadd (entlast) tap9))
(setq coords (list 
(list 2880.485 868.92) 
(list 2880.475 868.92) 
(list 2880.4745 868.9303) 
(list 2880.4723 868.9406) 
(list 2880.4686 868.9508) 
(list 2880.4633 868.9611) 
(list 2880.4568 868.9714) 
(list 2880.4491 868.9817) 
(list 2880.4405 868.9919) 
(list 2880.4313 869.0022) 
(list 2880.4217 869.0125) 
(list 2880.412 869.0228) 
(list 2880.4025 869.0331) 
(list 2880.3935 869.0433) 
(list 2880.3853 869.0536) 
(list 2880.3781 869.0639) 
(list 2880.3722 869.0742) 
(list 2880.3678 869.0844) 
(list 2880.365 869.0947) 
(list 2880.3639 869.105) 
(list 2880.3645 869.1153) 
(list 2880.367 869.1256) 
(list 2880.3711 869.1358) 
(list 2880.3768 869.1461) 
(list 2880.384 869.1564) 
(list 2880.3923 869.1667) 
(list 2880.4017 869.1769) 
(list 2880.4117 869.1872) 
(list 2880.4222 869.1975) 
(list 2880.4327 869.2078) 
(list 2880.4431 869.2181) 
(list 2880.4528 869.2283) 
(list 2880.4617 869.2386) 
(list 2880.4695 869.2489) 
(list 2880.4759 869.2592) 
(list 2880.4807 869.2694) 
(list 2880.4838 869.2797) 
(list 2880.485 869.29) 
(list 2880.485 869.29)))
(apply 'command (append '("pline") coords '("c")))
(setq tap9 (ssadd (entlast) tap9))
(command "_mirror" (entlast) "" "2880,900" "2880,901" "No")
(setq tap9 (ssadd (entlast) tap9))
(setq coords (list 
(list 2881.13 868.92) 
(list 2880.485 868.92) 
(list 2880.485 868.9303) 
(list 2880.485 868.9406) 
(list 2880.485 868.9508) 
(list 2880.485 868.9611) 
(list 2880.485 868.9714) 
(list 2880.485 868.9817) 
(list 2880.485 868.9919) 
(list 2880.485 869.0022) 
(list 2880.485 869.0125) 
(list 2880.485 869.0228) 
(list 2880.485 869.0331) 
(list 2880.485 869.0433) 
(list 2880.485 869.0536) 
(list 2880.485 869.0639) 
(list 2880.485 869.0742) 
(list 2880.485 869.0844) 
(list 2880.485 869.0947) 
(list 2880.485 869.105) 
(list 2880.485 869.1153) 
(list 2880.485 869.1256) 
(list 2880.485 869.1358) 
(list 2880.485 869.1461) 
(list 2880.485 869.1564) 
(list 2880.485 869.1667) 
(list 2880.485 869.1769) 
(list 2880.485 869.1872) 
(list 2880.485 869.1975) 
(list 2880.485 869.2078) 
(list 2880.485 869.2181) 
(list 2880.485 869.2283) 
(list 2880.485 869.2386) 
(list 2880.485 869.2489) 
(list 2880.485 869.2592) 
(list 2880.485 869.2694) 
(list 2880.485 869.2797) 
(list 2880.485 869.29) 
(list 2881.13 869.29)))
(apply 'command (append '("pline") coords '("c")))
(setq tap9 (ssadd (entlast) tap9))
(command "_mirror" (entlast) "" "2880,900" "2880,901" "No")
(setq tap9 (ssadd (entlast) tap9))
(setq coords (list 
(list 2880 869.29) 
(list 2880.135 869.29) 
(list 2880.135 869.3003) 
(list 2880.135 869.3106) 
(list 2880.135 869.3208) 
(list 2880.135 869.3311) 
(list 2880.135 869.3414) 
(list 2880.135 869.3517) 
(list 2880.135 869.3619) 
(list 2880.135 869.3722) 
(list 2880.135 869.3825) 
(list 2880.135 869.3928) 
(list 2880.135 869.4031) 
(list 2880.135 869.4133) 
(list 2880.135 869.4236) 
(list 2880.135 869.4339) 
(list 2880.135 869.4442) 
(list 2880.135 869.4544) 
(list 2880.135 869.4647) 
(list 2880.135 869.475) 
(list 2880.135 869.4853) 
(list 2880.135 869.4956) 
(list 2880.135 869.5058) 
(list 2880.135 869.5161) 
(list 2880.135 869.5264) 
(list 2880.135 869.5367) 
(list 2880.135 869.5469) 
(list 2880.135 869.5572) 
(list 2880.135 869.5675) 
(list 2880.135 869.5778) 
(list 2880.135 869.5881) 
(list 2880.135 869.5983) 
(list 2880.135 869.6086) 
(list 2880.135 869.6189) 
(list 2880.135 869.6292) 
(list 2880.135 869.6394) 
(list 2880.135 869.6497) 
(list 2880.135 869.66) 
(list 2880 869.66)))
(apply 'command (append '("pline") coords '("c")))
(setq tap9 (ssadd (entlast) tap9))
(command "_mirror" (entlast) "" "2880,900" "2880,901" "No")
(setq tap9 (ssadd (entlast) tap9))
(setq coords (list 
(list 2880.495 869.29) 
(list 2880.485 869.29) 
(list 2880.4843 869.3003) 
(list 2880.4818 869.3106) 
(list 2880.4774 869.3208) 
(list 2880.4712 869.3311) 
(list 2880.4636 869.3414) 
(list 2880.4547 869.3517) 
(list 2880.4447 869.3619) 
(list 2880.4339 869.3722) 
(list 2880.4227 869.3825) 
(list 2880.4115 869.3928) 
(list 2880.4005 869.4031) 
(list 2880.3901 869.4133) 
(list 2880.3806 869.4236) 
(list 2880.3723 869.4339) 
(list 2880.3655 869.4442) 
(list 2880.3604 869.4544) 
(list 2880.3572 869.4647) 
(list 2880.356 869.475) 
(list 2880.3568 869.4853) 
(list 2880.3596 869.4956) 
(list 2880.3644 869.5058) 
(list 2880.371 869.5161) 
(list 2880.3793 869.5264) 
(list 2880.3889 869.5367) 
(list 2880.3997 869.5469) 
(list 2880.4113 869.5572) 
(list 2880.4233 869.5675) 
(list 2880.4354 869.5778) 
(list 2880.4472 869.5881) 
(list 2880.4583 869.5983) 
(list 2880.4685 869.6086) 
(list 2880.4774 869.6189) 
(list 2880.4847 869.6292) 
(list 2880.4902 869.6394) 
(list 2880.4936 869.6497) 
(list 2880.495 869.66) 
(list 2880.495 869.66)))
(apply 'command (append '("pline") coords '("c")))
(setq tap9 (ssadd (entlast) tap9))
(command "_mirror" (entlast) "" "2880,900" "2880,901" "No")
(setq tap9 (ssadd (entlast) tap9))
(setq coords (list 
(list 2881.13 869.29) 
(list 2880.495 869.29) 
(list 2880.495 869.3003) 
(list 2880.495 869.3106) 
(list 2880.495 869.3208) 
(list 2880.495 869.3311) 
(list 2880.495 869.3414) 
(list 2880.495 869.3517) 
(list 2880.495 869.3619) 
(list 2880.495 869.3722) 
(list 2880.495 869.3825) 
(list 2880.495 869.3928) 
(list 2880.495 869.4031) 
(list 2880.495 869.4133) 
(list 2880.495 869.4236) 
(list 2880.495 869.4339) 
(list 2880.495 869.4442) 
(list 2880.495 869.4544) 
(list 2880.495 869.4647) 
(list 2880.495 869.475) 
(list 2880.495 869.4853) 
(list 2880.495 869.4956) 
(list 2880.495 869.5058) 
(list 2880.495 869.5161) 
(list 2880.495 869.5264) 
(list 2880.495 869.5367) 
(list 2880.495 869.5469) 
(list 2880.495 869.5572) 
(list 2880.495 869.5675) 
(list 2880.495 869.5778) 
(list 2880.495 869.5881) 
(list 2880.495 869.5983) 
(list 2880.495 869.6086) 
(list 2880.495 869.6189) 
(list 2880.495 869.6292) 
(list 2880.495 869.6394) 
(list 2880.495 869.6497) 
(list 2880.495 869.66) 
(list 2881.13 869.66)))
(apply 'command (append '("pline") coords '("c")))
(setq tap9 (ssadd (entlast) tap9))
(command "_mirror" (entlast) "" "2880,900" "2880,901" "No")
(setq tap9 (ssadd (entlast) tap9))
(setq coords (list 
(list 2880 869.66) 
(list 2880.135 869.66) 
(list 2880.135 869.6703) 
(list 2880.135 869.6806) 
(list 2880.135 869.6908) 
(list 2880.135 869.7011) 
(list 2880.135 869.7114) 
(list 2880.135 869.7217) 
(list 2880.135 869.7319) 
(list 2880.135 869.7422) 
(list 2880.135 869.7525) 
(list 2880.135 869.7628) 
(list 2880.135 869.7731) 
(list 2880.135 869.7833) 
(list 2880.135 869.7936) 
(list 2880.135 869.8039) 
(list 2880.135 869.8142) 
(list 2880.135 869.8244) 
(list 2880.135 869.8347) 
(list 2880.135 869.845) 
(list 2880.135 869.8553) 
(list 2880.135 869.8656) 
(list 2880.135 869.8758) 
(list 2880.135 869.8861) 
(list 2880.135 869.8964) 
(list 2880.135 869.9067) 
(list 2880.135 869.9169) 
(list 2880.135 869.9272) 
(list 2880.135 869.9375) 
(list 2880.135 869.9478) 
(list 2880.135 869.9581) 
(list 2880.135 869.9683) 
(list 2880.135 869.9786) 
(list 2880.135 869.9889) 
(list 2880.135 869.9992) 
(list 2880.135 870.0094) 
(list 2880.135 870.0197) 
(list 2880.135 870.03) 
(list 2880 870.03)))
(apply 'command (append '("pline") coords '("c")))
(setq tap9 (ssadd (entlast) tap9))
(command "_mirror" (entlast) "" "2880,900" "2880,901" "No")
(setq tap9 (ssadd (entlast) tap9))
(setq coords (list 
(list 2880.505 869.66) 
(list 2880.495 869.66) 
(list 2880.4942 869.6703) 
(list 2880.4912 869.6806) 
(list 2880.4862 869.6908) 
(list 2880.4792 869.7011) 
(list 2880.4704 869.7114) 
(list 2880.4602 869.7217) 
(list 2880.4488 869.7319) 
(list 2880.4365 869.7422) 
(list 2880.4238 869.7525) 
(list 2880.411 869.7628) 
(list 2880.3985 869.7731) 
(list 2880.3867 869.7833) 
(list 2880.3759 869.7936) 
(list 2880.3665 869.8039) 
(list 2880.3589 869.8142) 
(list 2880.3531 869.8244) 
(list 2880.3495 869.8347) 
(list 2880.3481 869.845) 
(list 2880.3491 869.8553) 
(list 2880.3523 869.8656) 
(list 2880.3578 869.8758) 
(list 2880.3653 869.8861) 
(list 2880.3746 869.8964) 
(list 2880.3855 869.9067) 
(list 2880.3977 869.9169) 
(list 2880.4108 869.9272) 
(list 2880.4243 869.9375) 
(list 2880.438 869.9478) 
(list 2880.4513 869.9581) 
(list 2880.4639 869.9683) 
(list 2880.4753 869.9786) 
(list 2880.4853 869.9889) 
(list 2880.4935 869.9992) 
(list 2880.4996 870.0094) 
(list 2880.5035 870.0197) 
(list 2880.505 870.03) 
(list 2880.505 870.03)))
(apply 'command (append '("pline") coords '("c")))
(setq tap9 (ssadd (entlast) tap9))
(command "_mirror" (entlast) "" "2880,900" "2880,901" "No")
(setq tap9 (ssadd (entlast) tap9))
(setq coords (list 
(list 2881.13 869.66) 
(list 2880.505 869.66) 
(list 2880.505 869.6703) 
(list 2880.505 869.6806) 
(list 2880.505 869.6908) 
(list 2880.505 869.7011) 
(list 2880.505 869.7114) 
(list 2880.505 869.7217) 
(list 2880.505 869.7319) 
(list 2880.505 869.7422) 
(list 2880.505 869.7525) 
(list 2880.505 869.7628) 
(list 2880.505 869.7731) 
(list 2880.505 869.7833) 
(list 2880.505 869.7936) 
(list 2880.505 869.8039) 
(list 2880.505 869.8142) 
(list 2880.505 869.8244) 
(list 2880.505 869.8347) 
(list 2880.505 869.845) 
(list 2880.505 869.8553) 
(list 2880.505 869.8656) 
(list 2880.505 869.8758) 
(list 2880.505 869.8861) 
(list 2880.505 869.8964) 
(list 2880.505 869.9067) 
(list 2880.505 869.9169) 
(list 2880.505 869.9272) 
(list 2880.505 869.9375) 
(list 2880.505 869.9478) 
(list 2880.505 869.9581) 
(list 2880.505 869.9683) 
(list 2880.505 869.9786) 
(list 2880.505 869.9889) 
(list 2880.505 869.9992) 
(list 2880.505 870.0094) 
(list 2880.505 870.0197) 
(list 2880.505 870.03) 
(list 2881.13 870.03)))
(apply 'command (append '("pline") coords '("c")))
(setq tap9 (ssadd (entlast) tap9))
(command "_mirror" (entlast) "" "2880,900" "2880,901" "No")
(setq tap9 (ssadd (entlast) tap9))
(setq coords (list 
(list 2880 870.03) 
(list 2880.135 870.03) 
(list 2880.135 870.0403) 
(list 2880.135 870.0506) 
(list 2880.135 870.0608) 
(list 2880.135 870.0711) 
(list 2880.135 870.0814) 
(list 2880.135 870.0917) 
(list 2880.135 870.1019) 
(list 2880.135 870.1122) 
(list 2880.135 870.1225) 
(list 2880.135 870.1328) 
(list 2880.135 870.1431) 
(list 2880.135 870.1533) 
(list 2880.135 870.1636) 
(list 2880.135 870.1739) 
(list 2880.135 870.1842) 
(list 2880.135 870.1944) 
(list 2880.135 870.2047) 
(list 2880.135 870.215) 
(list 2880.135 870.2253) 
(list 2880.135 870.2356) 
(list 2880.135 870.2458) 
(list 2880.135 870.2561) 
(list 2880.135 870.2664) 
(list 2880.135 870.2767) 
(list 2880.135 870.2869) 
(list 2880.135 870.2972) 
(list 2880.135 870.3075) 
(list 2880.135 870.3178) 
(list 2880.135 870.3281) 
(list 2880.135 870.3383) 
(list 2880.135 870.3486) 
(list 2880.135 870.3589) 
(list 2880.135 870.3692) 
(list 2880.135 870.3794) 
(list 2880.135 870.3897) 
(list 2880.135 870.4) 
(list 2880 870.4)))
(apply 'command (append '("pline") coords '("c")))
(setq tap9 (ssadd (entlast) tap9))
(command "_mirror" (entlast) "" "2880,900" "2880,901" "No")
(setq tap9 (ssadd (entlast) tap9))
(setq coords (list 
(list 2880.515 870.03) 
(list 2880.505 870.03) 
(list 2880.5041 870.0403) 
(list 2880.5007 870.0506) 
(list 2880.495 870.0608) 
(list 2880.4871 870.0711) 
(list 2880.4772 870.0814) 
(list 2880.4657 870.0917) 
(list 2880.4529 870.1019) 
(list 2880.4391 870.1122) 
(list 2880.4249 870.1225) 
(list 2880.4105 870.1328) 
(list 2880.3965 870.1431) 
(list 2880.3833 870.1533) 
(list 2880.3712 870.1636) 
(list 2880.3608 870.1739) 
(list 2880.3522 870.1842) 
(list 2880.3458 870.1944) 
(list 2880.3418 870.2047) 
(list 2880.3403 870.215) 
(list 2880.3413 870.2253) 
(list 2880.345 870.2356) 
(list 2880.3511 870.2458) 
(list 2880.3595 870.2561) 
(list 2880.3699 870.2664) 
(list 2880.3821 870.2767) 
(list 2880.3957 870.2869) 
(list 2880.4103 870.2972) 
(list 2880.4254 870.3075) 
(list 2880.4406 870.3178) 
(list 2880.4554 870.3281) 
(list 2880.4694 870.3383) 
(list 2880.4821 870.3486) 
(list 2880.4932 870.3589) 
(list 2880.5023 870.3692) 
(list 2880.5091 870.3794) 
(list 2880.5134 870.3897) 
(list 2880.515 870.4) 
(list 2880.515 870.4)))
(apply 'command (append '("pline") coords '("c")))
(setq tap9 (ssadd (entlast) tap9))
(command "_mirror" (entlast) "" "2880,900" "2880,901" "No")
(setq tap9 (ssadd (entlast) tap9))
(setq coords (list 
(list 2881.13 870.03) 
(list 2880.515 870.03) 
(list 2880.515 870.0403) 
(list 2880.515 870.0506) 
(list 2880.515 870.0608) 
(list 2880.515 870.0711) 
(list 2880.515 870.0814) 
(list 2880.515 870.0917) 
(list 2880.515 870.1019) 
(list 2880.515 870.1122) 
(list 2880.515 870.1225) 
(list 2880.515 870.1328) 
(list 2880.515 870.1431) 
(list 2880.515 870.1533) 
(list 2880.515 870.1636) 
(list 2880.515 870.1739) 
(list 2880.515 870.1842) 
(list 2880.515 870.1944) 
(list 2880.515 870.2047) 
(list 2880.515 870.215) 
(list 2880.515 870.2253) 
(list 2880.515 870.2356) 
(list 2880.515 870.2458) 
(list 2880.515 870.2561) 
(list 2880.515 870.2664) 
(list 2880.515 870.2767) 
(list 2880.515 870.2869) 
(list 2880.515 870.2972) 
(list 2880.515 870.3075) 
(list 2880.515 870.3178) 
(list 2880.515 870.3281) 
(list 2880.515 870.3383) 
(list 2880.515 870.3486) 
(list 2880.515 870.3589) 
(list 2880.515 870.3692) 
(list 2880.515 870.3794) 
(list 2880.515 870.3897) 
(list 2880.515 870.4) 
(list 2881.13 870.4)))
(apply 'command (append '("pline") coords '("c")))
(setq tap9 (ssadd (entlast) tap9))
(command "_mirror" (entlast) "" "2880,900" "2880,901" "No")
(setq tap9 (ssadd (entlast) tap9))
(setq coords (list 
(list 2880 870.4) 
(list 2880.135 870.4) 
(list 2880.135 870.4103) 
(list 2880.135 870.4206) 
(list 2880.135 870.4308) 
(list 2880.135 870.4411) 
(list 2880.135 870.4514) 
(list 2880.135 870.4617) 
(list 2880.135 870.4719) 
(list 2880.135 870.4822) 
(list 2880.135 870.4925) 
(list 2880.135 870.5028) 
(list 2880.135 870.5131) 
(list 2880.135 870.5233) 
(list 2880.135 870.5336) 
(list 2880.135 870.5439) 
(list 2880.135 870.5542) 
(list 2880.135 870.5644) 
(list 2880.135 870.5747) 
(list 2880.135 870.585) 
(list 2880.135 870.5953) 
(list 2880.135 870.6056) 
(list 2880.135 870.6158) 
(list 2880.135 870.6261) 
(list 2880.135 870.6364) 
(list 2880.135 870.6467) 
(list 2880.135 870.6569) 
(list 2880.135 870.6672) 
(list 2880.135 870.6775) 
(list 2880.135 870.6878) 
(list 2880.135 870.6981) 
(list 2880.135 870.7083) 
(list 2880.135 870.7186) 
(list 2880.135 870.7289) 
(list 2880.135 870.7392) 
(list 2880.135 870.7494) 
(list 2880.135 870.7597) 
(list 2880.135 870.77) 
(list 2880 870.77)))
(apply 'command (append '("pline") coords '("c")))
(setq tap9 (ssadd (entlast) tap9))
(command "_mirror" (entlast) "" "2880,900" "2880,901" "No")
(setq tap9 (ssadd (entlast) tap9))
(setq coords (list 
(list 2880.525 870.4) 
(list 2880.515 870.4) 
(list 2880.5139 870.4103) 
(list 2880.5101 870.4206) 
(list 2880.5038 870.4308) 
(list 2880.495 870.4411) 
(list 2880.484 870.4514) 
(list 2880.4713 870.4617) 
(list 2880.457 870.4719) 
(list 2880.4418 870.4822) 
(list 2880.4259 870.4925) 
(list 2880.41 870.5028) 
(list 2880.3945 870.5131) 
(list 2880.3799 870.5233) 
(list 2880.3666 870.5336) 
(list 2880.355 870.5439) 
(list 2880.3455 870.5542) 
(list 2880.3385 870.5644) 
(list 2880.334 870.5747) 
(list 2880.3324 870.585) 
(list 2880.3336 870.5953) 
(list 2880.3376 870.6056) 
(list 2880.3444 870.6158) 
(list 2880.3537 870.6261) 
(list 2880.3653 870.6364) 
(list 2880.3787 870.6467) 
(list 2880.3937 870.6569) 
(list 2880.4098 870.6672) 
(list 2880.4265 870.6775) 
(list 2880.4432 870.6878) 
(list 2880.4595 870.6981) 
(list 2880.4749 870.7083) 
(list 2880.489 870.7186) 
(list 2880.5011 870.7289) 
(list 2880.5111 870.7392) 
(list 2880.5185 870.7494) 
(list 2880.5232 870.7597) 
(list 2880.525 870.77) 
(list 2880.525 870.77)))
(apply 'command (append '("pline") coords '("c")))
(setq tap9 (ssadd (entlast) tap9))
(command "_mirror" (entlast) "" "2880,900" "2880,901" "No")
(setq tap9 (ssadd (entlast) tap9))
(setq coords (list 
(list 2881.13 870.4) 
(list 2880.525 870.4) 
(list 2880.525 870.4103) 
(list 2880.525 870.4206) 
(list 2880.525 870.4308) 
(list 2880.525 870.4411) 
(list 2880.525 870.4514) 
(list 2880.525 870.4617) 
(list 2880.525 870.4719) 
(list 2880.525 870.4822) 
(list 2880.525 870.4925) 
(list 2880.525 870.5028) 
(list 2880.525 870.5131) 
(list 2880.525 870.5233) 
(list 2880.525 870.5336) 
(list 2880.525 870.5439) 
(list 2880.525 870.5542) 
(list 2880.525 870.5644) 
(list 2880.525 870.5747) 
(list 2880.525 870.585) 
(list 2880.525 870.5953) 
(list 2880.525 870.6056) 
(list 2880.525 870.6158) 
(list 2880.525 870.6261) 
(list 2880.525 870.6364) 
(list 2880.525 870.6467) 
(list 2880.525 870.6569) 
(list 2880.525 870.6672) 
(list 2880.525 870.6775) 
(list 2880.525 870.6878) 
(list 2880.525 870.6981) 
(list 2880.525 870.7083) 
(list 2880.525 870.7186) 
(list 2880.525 870.7289) 
(list 2880.525 870.7392) 
(list 2880.525 870.7494) 
(list 2880.525 870.7597) 
(list 2880.525 870.77) 
(list 2881.13 870.77)))
(apply 'command (append '("pline") coords '("c")))
(setq tap9 (ssadd (entlast) tap9))
(command "_mirror" (entlast) "" "2880,900" "2880,901" "No")
(setq tap9 (ssadd (entlast) tap9))
(setq coords (list 
(list 2880 870.77) 
(list 2880.135 870.77) 
(list 2880.135 870.7803) 
(list 2880.135 870.7906) 
(list 2880.135 870.8008) 
(list 2880.135 870.8111) 
(list 2880.135 870.8214) 
(list 2880.135 870.8317) 
(list 2880.135 870.8419) 
(list 2880.135 870.8522) 
(list 2880.135 870.8625) 
(list 2880.135 870.8728) 
(list 2880.135 870.8831) 
(list 2880.135 870.8933) 
(list 2880.135 870.9036) 
(list 2880.135 870.9139) 
(list 2880.135 870.9242) 
(list 2880.135 870.9344) 
(list 2880.135 870.9447) 
(list 2880.135 870.955) 
(list 2880.135 870.9653) 
(list 2880.135 870.9756) 
(list 2880.135 870.9858) 
(list 2880.135 870.9961) 
(list 2880.135 871.0064) 
(list 2880.135 871.0167) 
(list 2880.135 871.0269) 
(list 2880.135 871.0372) 
(list 2880.135 871.0475) 
(list 2880.135 871.0578) 
(list 2880.135 871.0681) 
(list 2880.135 871.0783) 
(list 2880.135 871.0886) 
(list 2880.135 871.0989) 
(list 2880.135 871.1092) 
(list 2880.135 871.1194) 
(list 2880.135 871.1297) 
(list 2880.135 871.14) 
(list 2880 871.14)))
(apply 'command (append '("pline") coords '("c")))
(setq tap9 (ssadd (entlast) tap9))
(command "_mirror" (entlast) "" "2880,900" "2880,901" "No")
(setq tap9 (ssadd (entlast) tap9))
(setq coords (list 
(list 2880.535 870.77) 
(list 2880.525 870.77) 
(list 2880.5238 870.7803) 
(list 2880.5196 870.7906) 
(list 2880.5126 870.8008) 
(list 2880.5029 870.8111) 
(list 2880.4908 870.8214) 
(list 2880.4768 870.8317) 
(list 2880.4611 870.8419) 
(list 2880.4444 870.8522) 
(list 2880.427 870.8625) 
(list 2880.4095 870.8728) 
(list 2880.3925 870.8831) 
(list 2880.3765 870.8933) 
(list 2880.3619 870.9036) 
(list 2880.3492 870.9139) 
(list 2880.3389 870.9242) 
(list 2880.3311 870.9344) 
(list 2880.3263 870.9447) 
(list 2880.3245 870.955) 
(list 2880.3259 870.9653) 
(list 2880.3303 870.9756) 
(list 2880.3377 870.9858) 
(list 2880.3479 870.9961) 
(list 2880.3606 871.0064) 
(list 2880.3753 871.0167) 
(list 2880.3917 871.0269) 
(list 2880.4093 871.0372) 
(list 2880.4275 871.0475) 
(list 2880.4458 871.0578) 
(list 2880.4637 871.0681) 
(list 2880.4805 871.0783) 
(list 2880.4958 871.0886) 
(list 2880.509 871.0989) 
(list 2880.5199 871.1092) 
(list 2880.528 871.1194) 
(list 2880.5331 871.1297) 
(list 2880.535 871.14) 
(list 2880.535 871.14)))
(apply 'command (append '("pline") coords '("c")))
(setq tap9 (ssadd (entlast) tap9))
(command "_mirror" (entlast) "" "2880,900" "2880,901" "No")
(setq tap9 (ssadd (entlast) tap9))
(setq coords (list 
(list 2881.13 870.77) 
(list 2880.535 870.77) 
(list 2880.535 870.7803) 
(list 2880.535 870.7906) 
(list 2880.535 870.8008) 
(list 2880.535 870.8111) 
(list 2880.535 870.8214) 
(list 2880.535 870.8317) 
(list 2880.535 870.8419) 
(list 2880.535 870.8522) 
(list 2880.535 870.8625) 
(list 2880.535 870.8728) 
(list 2880.535 870.8831) 
(list 2880.535 870.8933) 
(list 2880.535 870.9036) 
(list 2880.535 870.9139) 
(list 2880.535 870.9242) 
(list 2880.535 870.9344) 
(list 2880.535 870.9447) 
(list 2880.535 870.955) 
(list 2880.535 870.9653) 
(list 2880.535 870.9756) 
(list 2880.535 870.9858) 
(list 2880.535 870.9961) 
(list 2880.535 871.0064) 
(list 2880.535 871.0167) 
(list 2880.535 871.0269) 
(list 2880.535 871.0372) 
(list 2880.535 871.0475) 
(list 2880.535 871.0578) 
(list 2880.535 871.0681) 
(list 2880.535 871.0783) 
(list 2880.535 871.0886) 
(list 2880.535 871.0989) 
(list 2880.535 871.1092) 
(list 2880.535 871.1194) 
(list 2880.535 871.1297) 
(list 2880.535 871.14) 
(list 2881.13 871.14)))
(apply 'command (append '("pline") coords '("c")))
(setq tap9 (ssadd (entlast) tap9))
(command "_mirror" (entlast) "" "2880,900" "2880,901" "No")
(setq tap9 (ssadd (entlast) tap9))
(setq coords (list 
(list 2880 871.14) 
(list 2880.135 871.14) 
(list 2880.135 871.1503) 
(list 2880.135 871.1606) 
(list 2880.135 871.1708) 
(list 2880.135 871.1811) 
(list 2880.135 871.1914) 
(list 2880.135 871.2017) 
(list 2880.135 871.2119) 
(list 2880.135 871.2222) 
(list 2880.135 871.2325) 
(list 2880.135 871.2428) 
(list 2880.135 871.2531) 
(list 2880.135 871.2633) 
(list 2880.135 871.2736) 
(list 2880.135 871.2839) 
(list 2880.135 871.2942) 
(list 2880.135 871.3044) 
(list 2880.135 871.3147) 
(list 2880.135 871.325) 
(list 2880.135 871.3353) 
(list 2880.135 871.3456) 
(list 2880.135 871.3558) 
(list 2880.135 871.3661) 
(list 2880.135 871.3764) 
(list 2880.135 871.3867) 
(list 2880.135 871.3969) 
(list 2880.135 871.4072) 
(list 2880.135 871.4175) 
(list 2880.135 871.4278) 
(list 2880.135 871.4381) 
(list 2880.135 871.4483) 
(list 2880.135 871.4586) 
(list 2880.135 871.4689) 
(list 2880.135 871.4792) 
(list 2880.135 871.4894) 
(list 2880.135 871.4997) 
(list 2880.135 871.51) 
(list 2880 871.51)))
(apply 'command (append '("pline") coords '("c")))
(setq tap9 (ssadd (entlast) tap9))
(command "_mirror" (entlast) "" "2880,900" "2880,901" "No")
(setq tap9 (ssadd (entlast) tap9))
(setq coords (list 
(list 2880.545 871.14) 
(list 2880.535 871.14) 
(list 2880.5336 871.1503) 
(list 2880.5291 871.1606) 
(list 2880.5214 871.1708) 
(list 2880.5108 871.1811) 
(list 2880.4977 871.1914) 
(list 2880.4823 871.2017) 
(list 2880.4653 871.2119) 
(list 2880.447 871.2222) 
(list 2880.4281 871.2325) 
(list 2880.4091 871.2428) 
(list 2880.3905 871.2531) 
(list 2880.3731 871.2633) 
(list 2880.3572 871.2736) 
(list 2880.3434 871.2839) 
(list 2880.3322 871.2942) 
(list 2880.3238 871.3044) 
(list 2880.3186 871.3147) 
(list 2880.3167 871.325) 
(list 2880.3181 871.3353) 
(list 2880.323 871.3456) 
(list 2880.3311 871.3558) 
(list 2880.3422 871.3661) 
(list 2880.3559 871.3764) 
(list 2880.3719 871.3867) 
(list 2880.3898 871.3969) 
(list 2880.4088 871.4072) 
(list 2880.4286 871.4175) 
(list 2880.4485 871.4278) 
(list 2880.4678 871.4381) 
(list 2880.486 871.4483) 
(list 2880.5026 871.4586) 
(list 2880.517 871.4689) 
(list 2880.5287 871.4792) 
(list 2880.5375 871.4894) 
(list 2880.543 871.4997) 
(list 2880.545 871.51) 
(list 2880.545 871.51)))
(apply 'command (append '("pline") coords '("c")))
(setq tap9 (ssadd (entlast) tap9))
(command "_mirror" (entlast) "" "2880,900" "2880,901" "No")
(setq tap9 (ssadd (entlast) tap9))
(setq coords (list 
(list 2881.13 871.14) 
(list 2880.545 871.14) 
(list 2880.545 871.1503) 
(list 2880.545 871.1606) 
(list 2880.545 871.1708) 
(list 2880.545 871.1811) 
(list 2880.545 871.1914) 
(list 2880.545 871.2017) 
(list 2880.545 871.2119) 
(list 2880.545 871.2222) 
(list 2880.545 871.2325) 
(list 2880.545 871.2428) 
(list 2880.545 871.2531) 
(list 2880.545 871.2633) 
(list 2880.545 871.2736) 
(list 2880.545 871.2839) 
(list 2880.545 871.2942) 
(list 2880.545 871.3044) 
(list 2880.545 871.3147) 
(list 2880.545 871.325) 
(list 2880.545 871.3353) 
(list 2880.545 871.3456) 
(list 2880.545 871.3558) 
(list 2880.545 871.3661) 
(list 2880.545 871.3764) 
(list 2880.545 871.3867) 
(list 2880.545 871.3969) 
(list 2880.545 871.4072) 
(list 2880.545 871.4175) 
(list 2880.545 871.4278) 
(list 2880.545 871.4381) 
(list 2880.545 871.4483) 
(list 2880.545 871.4586) 
(list 2880.545 871.4689) 
(list 2880.545 871.4792) 
(list 2880.545 871.4894) 
(list 2880.545 871.4997) 
(list 2880.545 871.51) 
(list 2881.13 871.51)))
(apply 'command (append '("pline") coords '("c")))
(setq tap9 (ssadd (entlast) tap9))
(command "_mirror" (entlast) "" "2880,900" "2880,901" "No")
(setq tap9 (ssadd (entlast) tap9))
(setq coords (list 
(list 2880 871.51) 
(list 2880.135 871.51) 
(list 2880.135 871.5203) 
(list 2880.135 871.5306) 
(list 2880.135 871.5408) 
(list 2880.135 871.5511) 
(list 2880.135 871.5614) 
(list 2880.135 871.5717) 
(list 2880.135 871.5819) 
(list 2880.135 871.5922) 
(list 2880.135 871.6025) 
(list 2880.135 871.6128) 
(list 2880.135 871.6231) 
(list 2880.135 871.6333) 
(list 2880.135 871.6436) 
(list 2880.135 871.6539) 
(list 2880.135 871.6642) 
(list 2880.135 871.6744) 
(list 2880.135 871.6847) 
(list 2880.135 871.695) 
(list 2880.135 871.7053) 
(list 2880.135 871.7156) 
(list 2880.135 871.7258) 
(list 2880.135 871.7361) 
(list 2880.135 871.7464) 
(list 2880.135 871.7567) 
(list 2880.135 871.7669) 
(list 2880.135 871.7772) 
(list 2880.135 871.7875) 
(list 2880.135 871.7978) 
(list 2880.135 871.8081) 
(list 2880.135 871.8183) 
(list 2880.135 871.8286) 
(list 2880.135 871.8389) 
(list 2880.135 871.8492) 
(list 2880.135 871.8594) 
(list 2880.135 871.8697) 
(list 2880.135 871.88) 
(list 2880 871.88)))
(apply 'command (append '("pline") coords '("c")))
(setq tap9 (ssadd (entlast) tap9))
(command "_mirror" (entlast) "" "2880,900" "2880,901" "No")
(setq tap9 (ssadd (entlast) tap9))
(setq coords (list 
(list 2880.555 871.51) 
(list 2880.545 871.51) 
(list 2880.5435 871.5203) 
(list 2880.5385 871.5306) 
(list 2880.5302 871.5408) 
(list 2880.5187 871.5511) 
(list 2880.5045 871.5614) 
(list 2880.4879 871.5717) 
(list 2880.4694 871.5819) 
(list 2880.4496 871.5922) 
(list 2880.4291 871.6025) 
(list 2880.4086 871.6128) 
(list 2880.3885 871.6231) 
(list 2880.3697 871.6333) 
(list 2880.3525 871.6436) 
(list 2880.3377 871.6539) 
(list 2880.3255 871.6642) 
(list 2880.3165 871.6744) 
(list 2880.3108 871.6847) 
(list 2880.3088 871.695) 
(list 2880.3104 871.7053) 
(list 2880.3157 871.7156) 
(list 2880.3244 871.7258) 
(list 2880.3364 871.7361) 
(list 2880.3512 871.7464) 
(list 2880.3685 871.7567) 
(list 2880.3878 871.7669) 
(list 2880.4084 871.7772) 
(list 2880.4297 871.7875) 
(list 2880.4511 871.7978) 
(list 2880.4719 871.8081) 
(list 2880.4915 871.8183) 
(list 2880.5094 871.8286) 
(list 2880.5249 871.8389) 
(list 2880.5375 871.8492) 
(list 2880.5469 871.8594) 
(list 2880.5528 871.8697) 
(list 2880.555 871.88) 
(list 2880.555 871.88)))
(apply 'command (append '("pline") coords '("c")))
(setq tap9 (ssadd (entlast) tap9))
(command "_mirror" (entlast) "" "2880,900" "2880,901" "No")
(setq tap9 (ssadd (entlast) tap9))
(setq coords (list 
(list 2881.13 871.51) 
(list 2880.555 871.51) 
(list 2880.555 871.5203) 
(list 2880.555 871.5306) 
(list 2880.555 871.5408) 
(list 2880.555 871.5511) 
(list 2880.555 871.5614) 
(list 2880.555 871.5717) 
(list 2880.555 871.5819) 
(list 2880.555 871.5922) 
(list 2880.555 871.6025) 
(list 2880.555 871.6128) 
(list 2880.555 871.6231) 
(list 2880.555 871.6333) 
(list 2880.555 871.6436) 
(list 2880.555 871.6539) 
(list 2880.555 871.6642) 
(list 2880.555 871.6744) 
(list 2880.555 871.6847) 
(list 2880.555 871.695) 
(list 2880.555 871.7053) 
(list 2880.555 871.7156) 
(list 2880.555 871.7258) 
(list 2880.555 871.7361) 
(list 2880.555 871.7464) 
(list 2880.555 871.7567) 
(list 2880.555 871.7669) 
(list 2880.555 871.7772) 
(list 2880.555 871.7875) 
(list 2880.555 871.7978) 
(list 2880.555 871.8081) 
(list 2880.555 871.8183) 
(list 2880.555 871.8286) 
(list 2880.555 871.8389) 
(list 2880.555 871.8492) 
(list 2880.555 871.8594) 
(list 2880.555 871.8697) 
(list 2880.555 871.88) 
(list 2881.13 871.88)))
(apply 'command (append '("pline") coords '("c")))
(setq tap9 (ssadd (entlast) tap9))
(command "_mirror" (entlast) "" "2880,900" "2880,901" "No")
(setq tap9 (ssadd (entlast) tap9))
(setq coords (list 
(list 2880 871.88) 
(list 2880.135 871.88) 
(list 2880.135 871.8903) 
(list 2880.135 871.9006) 
(list 2880.135 871.9108) 
(list 2880.135 871.9211) 
(list 2880.135 871.9314) 
(list 2880.135 871.9417) 
(list 2880.135 871.9519) 
(list 2880.135 871.9622) 
(list 2880.135 871.9725) 
(list 2880.135 871.9828) 
(list 2880.135 871.9931) 
(list 2880.135 872.0033) 
(list 2880.135 872.0136) 
(list 2880.135 872.0239) 
(list 2880.135 872.0342) 
(list 2880.135 872.0444) 
(list 2880.135 872.0547) 
(list 2880.135 872.065) 
(list 2880.135 872.0753) 
(list 2880.135 872.0856) 
(list 2880.135 872.0958) 
(list 2880.135 872.1061) 
(list 2880.135 872.1164) 
(list 2880.135 872.1267) 
(list 2880.135 872.1369) 
(list 2880.135 872.1472) 
(list 2880.135 872.1575) 
(list 2880.135 872.1678) 
(list 2880.135 872.1781) 
(list 2880.135 872.1883) 
(list 2880.135 872.1986) 
(list 2880.135 872.2089) 
(list 2880.135 872.2192) 
(list 2880.135 872.2294) 
(list 2880.135 872.2397) 
(list 2880.135 872.25) 
(list 2880 872.25)))
(apply 'command (append '("pline") coords '("c")))
(setq tap9 (ssadd (entlast) tap9))
(command "_mirror" (entlast) "" "2880,900" "2880,901" "No")
(setq tap9 (ssadd (entlast) tap9))
(setq coords (list 
(list 2880.565 871.88) 
(list 2880.555 871.88) 
(list 2880.5534 871.8903) 
(list 2880.548 871.9006) 
(list 2880.539 871.9108) 
(list 2880.5266 871.9211) 
(list 2880.5113 871.9314) 
(list 2880.4934 871.9417) 
(list 2880.4735 871.9519) 
(list 2880.4522 871.9622) 
(list 2880.4302 871.9725) 
(list 2880.4081 871.9828) 
(list 2880.3866 871.9931) 
(list 2880.3663 872.0033) 
(list 2880.3479 872.0136) 
(list 2880.3319 872.0239) 
(list 2880.3188 872.0342) 
(list 2880.3092 872.0444) 
(list 2880.3031 872.0547) 
(list 2880.3009 872.065) 
(list 2880.3027 872.0753) 
(list 2880.3083 872.0856) 
(list 2880.3177 872.0958) 
(list 2880.3306 872.1061) 
(list 2880.3466 872.1164) 
(list 2880.3651 872.1267) 
(list 2880.3858 872.1369) 
(list 2880.4079 872.1472) 
(list 2880.4307 872.1575) 
(list 2880.4537 872.1678) 
(list 2880.476 872.1781) 
(list 2880.4971 872.1883) 
(list 2880.5162 872.1986) 
(list 2880.5328 872.2089) 
(list 2880.5463 872.2192) 
(list 2880.5564 872.2294) 
(list 2880.5627 872.2397) 
(list 2880.565 872.25) 
(list 2880.565 872.25)))
(apply 'command (append '("pline") coords '("c")))
(setq tap9 (ssadd (entlast) tap9))
(command "_mirror" (entlast) "" "2880,900" "2880,901" "No")
(setq tap9 (ssadd (entlast) tap9))
(setq coords (list 
(list 2881.13 871.88) 
(list 2880.565 871.88) 
(list 2880.565 871.8903) 
(list 2880.565 871.9006) 
(list 2880.565 871.9108) 
(list 2880.565 871.9211) 
(list 2880.565 871.9314) 
(list 2880.565 871.9417) 
(list 2880.565 871.9519) 
(list 2880.565 871.9622) 
(list 2880.565 871.9725) 
(list 2880.565 871.9828) 
(list 2880.565 871.9931) 
(list 2880.565 872.0033) 
(list 2880.565 872.0136) 
(list 2880.565 872.0239) 
(list 2880.565 872.0342) 
(list 2880.565 872.0444) 
(list 2880.565 872.0547) 
(list 2880.565 872.065) 
(list 2880.565 872.0753) 
(list 2880.565 872.0856) 
(list 2880.565 872.0958) 
(list 2880.565 872.1061) 
(list 2880.565 872.1164) 
(list 2880.565 872.1267) 
(list 2880.565 872.1369) 
(list 2880.565 872.1472) 
(list 2880.565 872.1575) 
(list 2880.565 872.1678) 
(list 2880.565 872.1781) 
(list 2880.565 872.1883) 
(list 2880.565 872.1986) 
(list 2880.565 872.2089) 
(list 2880.565 872.2192) 
(list 2880.565 872.2294) 
(list 2880.565 872.2397) 
(list 2880.565 872.25) 
(list 2881.13 872.25)))
(apply 'command (append '("pline") coords '("c")))
(setq tap9 (ssadd (entlast) tap9))
(command "_mirror" (entlast) "" "2880,900" "2880,901" "No")
(setq tap9 (ssadd (entlast) tap9))
(command "_block" "blktap9" "2880,900" tap9 "")
(command "_insert" "blktap9" "2880,900" "1" "1" "0")
(command "_insert" "blktap9" "2880,900" "1" "1" "180")
(setq uc9 nil)
(setq uc9 (ssadd))
(setq coords (list 
(list 0 -0.185) 
(list 0.135 -0.185) 
(list 0.135 -0.17472) 
(list 0.135 -0.16444) 
(list 0.135 -0.15417) 
(list 0.135 -0.14389) 
(list 0.135 -0.13361) 
(list 0.135 -0.12333) 
(list 0.135 -0.11306) 
(list 0.135 -0.10278) 
(list 0.135 -0.0925) 
(list 0.135 -0.082222) 
(list 0.135 -0.071944) 
(list 0.135 -0.061667) 
(list 0.135 -0.051389) 
(list 0.135 -0.041111) 
(list 0.135 -0.030833) 
(list 0.135 -0.020556) 
(list 0.135 -0.010278) 
(list 0.135 0) 
(list 0.135 0.010278) 
(list 0.135 0.020556) 
(list 0.135 0.030833) 
(list 0.135 0.041111) 
(list 0.135 0.051389) 
(list 0.135 0.061667) 
(list 0.135 0.071944) 
(list 0.135 0.082222) 
(list 0.135 0.0925) 
(list 0.135 0.10278) 
(list 0.135 0.11306) 
(list 0.135 0.12333) 
(list 0.135 0.13361) 
(list 0.135 0.14389) 
(list 0.135 0.15417) 
(list 0.135 0.16444) 
(list 0.135 0.17472) 
(list 0.135 0.185) 
(list 0 0.185)))
(apply 'command (append '("pline") coords '("c")))
(setq uc9 (ssadd (entlast) uc9))
(setq coords (list 
(list 1.13 -0.185) 
(list 0.565 -0.185) 
(list 0.56296 -0.17472) 
(list 0.55692 -0.16444) 
(list 0.54705 -0.15417) 
(list 0.53365 -0.14389) 
(list 0.51713 -0.13361) 
(list 0.498 -0.12333) 
(list 0.47683 -0.11306) 
(list 0.45427 -0.10278) 
(list 0.431 -0.0925) 
(list 0.40773 -0.082222) 
(list 0.38517 -0.071944) 
(list 0.364 -0.061667) 
(list 0.34487 -0.051389) 
(list 0.32835 -0.041111) 
(list 0.31495 -0.030833) 
(list 0.30508 -0.020556) 
(list 0.29904 -0.010278) 
(list 0.297 0) 
(list 0.29904 0.010278) 
(list 0.30508 0.020556) 
(list 0.31495 0.030833) 
(list 0.32835 0.041111) 
(list 0.34487 0.051389) 
(list 0.364 0.061667) 
(list 0.38517 0.071944) 
(list 0.40773 0.082222) 
(list 0.431 0.0925) 
(list 0.45427 0.10278) 
(list 0.47683 0.11306) 
(list 0.498 0.12333) 
(list 0.51713 0.13361) 
(list 0.53365 0.14389) 
(list 0.54705 0.15417) 
(list 0.55692 0.16444) 
(list 0.56296 0.17472) 
(list 0.565 0.185) 
(list 1.13 0.185)))
(apply 'command (append '("pline") coords '("c")))
(setq uc9 (ssadd (entlast) uc9))
(command "_block" "blkuc9" "0,0.185" uc9 "")
(command "_insert" "blkuc9" "2880,872.62" "1" "1" "0")
(command "_insert" "blkuc9" "2880,872.25" "1" "1" "180")
(command "_insert" "blkuc9" "2880,872.99" "1" "1" "0")
(command "_insert" "blkuc9" "2880,872.62" "1" "1" "180")
(command "_insert" "blkuc9" "2880,873.36" "1" "1" "0")
(command "_insert" "blkuc9" "2880,872.99" "1" "1" "180")
(command "_insert" "blkuc9" "2880,873.73" "1" "1" "0")
(command "_insert" "blkuc9" "2880,873.36" "1" "1" "180")
(command "_insert" "blkuc9" "2880,874.1" "1" "1" "0")
(command "_insert" "blkuc9" "2880,873.73" "1" "1" "180")
(command "_insert" "blkuc9" "2880,874.47" "1" "1" "0")
(command "_insert" "blkuc9" "2880,874.1" "1" "1" "180")
(command "_insert" "blkuc9" "2880,874.84" "1" "1" "0")
(command "_insert" "blkuc9" "2880,874.47" "1" "1" "180")
(command "_insert" "blkuc9" "2880,875.21" "1" "1" "0")
(command "_insert" "blkuc9" "2880,874.84" "1" "1" "180")
(command "_insert" "blkuc9" "2880,875.58" "1" "1" "0")
(command "_insert" "blkuc9" "2880,875.21" "1" "1" "180")
(command "_insert" "blkuc9" "2880,875.95" "1" "1" "0")
(command "_insert" "blkuc9" "2880,875.58" "1" "1" "180")
(command "_insert" "blkuc9" "2880,876.32" "1" "1" "0")
(command "_insert" "blkuc9" "2880,875.95" "1" "1" "180")
(command "_insert" "blkuc9" "2880,876.69" "1" "1" "0")
(command "_insert" "blkuc9" "2880,876.32" "1" "1" "180")
(command "_insert" "blkuc9" "2880,877.06" "1" "1" "0")
(command "_insert" "blkuc9" "2880,876.69" "1" "1" "180")
(command "_insert" "blkuc9" "2880,877.43" "1" "1" "0")
(command "_insert" "blkuc9" "2880,877.06" "1" "1" "180")
(command "_insert" "blkuc9" "2880,877.8" "1" "1" "0")
(command "_insert" "blkuc9" "2880,877.43" "1" "1" "180")
(command "_insert" "blkuc9" "2880,878.17" "1" "1" "0")
(command "_insert" "blkuc9" "2880,877.8" "1" "1" "180")
(command "_insert" "blkuc9" "2880,878.54" "1" "1" "0")
(command "_insert" "blkuc9" "2880,878.17" "1" "1" "180")
(command "_insert" "blkuc9" "2880,878.91" "1" "1" "0")
(command "_insert" "blkuc9" "2880,878.54" "1" "1" "180")
(command "_insert" "blkuc9" "2880,879.28" "1" "1" "0")
(command "_insert" "blkuc9" "2880,878.91" "1" "1" "180")
(command "_insert" "blkuc9" "2880,879.65" "1" "1" "0")
(command "_insert" "blkuc9" "2880,879.28" "1" "1" "180")
(command "_insert" "blkuc9" "2880,880.02" "1" "1" "0")
(command "_insert" "blkuc9" "2880,879.65" "1" "1" "180")
(command "_insert" "blkuc9" "2880,880.39" "1" "1" "0")
(command "_insert" "blkuc9" "2880,880.02" "1" "1" "180")
(command "_insert" "blkuc9" "2880,880.76" "1" "1" "0")
(command "_insert" "blkuc9" "2880,880.39" "1" "1" "180")
(command "_insert" "blkuc9" "2880,881.13" "1" "1" "0")
(command "_insert" "blkuc9" "2880,880.76" "1" "1" "180")
(command "_insert" "blkuc9" "2880,881.5" "1" "1" "0")
(command "_insert" "blkuc9" "2880,881.13" "1" "1" "180")
(command "_insert" "blkuc9" "2880,881.87" "1" "1" "0")
(command "_insert" "blkuc9" "2880,881.5" "1" "1" "180")
(command "_insert" "blkuc9" "2880,882.24" "1" "1" "0")
(command "_insert" "blkuc9" "2880,881.87" "1" "1" "180")
(command "_insert" "blkuc9" "2880,882.61" "1" "1" "0")
(command "_insert" "blkuc9" "2880,882.24" "1" "1" "180")
(command "_insert" "blkuc9" "2880,882.98" "1" "1" "0")
(command "_insert" "blkuc9" "2880,882.61" "1" "1" "180")
(command "_insert" "blkuc9" "2880,883.35" "1" "1" "0")
(command "_insert" "blkuc9" "2880,882.98" "1" "1" "180")
(command "_insert" "blkuc9" "2880,883.72" "1" "1" "0")
(command "_insert" "blkuc9" "2880,883.35" "1" "1" "180")
(command "_insert" "blkuc9" "2880,884.09" "1" "1" "0")
(command "_insert" "blkuc9" "2880,883.72" "1" "1" "180")
(command "_insert" "blkuc9" "2880,884.46" "1" "1" "0")
(command "_insert" "blkuc9" "2880,884.09" "1" "1" "180")
(command "_insert" "blkuc9" "2880,884.83" "1" "1" "0")
(command "_insert" "blkuc9" "2880,884.46" "1" "1" "180")
(command "_insert" "blkuc9" "2880,885.2" "1" "1" "0")
(command "_insert" "blkuc9" "2880,884.83" "1" "1" "180")
(command "_insert" "blkuc9" "2880,885.57" "1" "1" "0")
(command "_insert" "blkuc9" "2880,885.2" "1" "1" "180")
(command "_insert" "blkuc9" "2880,885.94" "1" "1" "0")
(command "_insert" "blkuc9" "2880,885.57" "1" "1" "180")
(command "_insert" "blkuc9" "2880,886.31" "1" "1" "0")
(command "_insert" "blkuc9" "2880,885.94" "1" "1" "180")
(command "_insert" "blkuc9" "2880,886.68" "1" "1" "0")
(command "_insert" "blkuc9" "2880,886.31" "1" "1" "180")
(command "_insert" "blkuc9" "2880,887.05" "1" "1" "0")
(command "_insert" "blkuc9" "2880,886.68" "1" "1" "180")
(command "_insert" "blkuc9" "2880,887.42" "1" "1" "0")
(command "_insert" "blkuc9" "2880,887.05" "1" "1" "180")
(command "_insert" "blkuc9" "2880,887.79" "1" "1" "0")
(command "_insert" "blkuc9" "2880,887.42" "1" "1" "180")
(command "_insert" "blkuc9" "2880,888.16" "1" "1" "0")
(command "_insert" "blkuc9" "2880,887.79" "1" "1" "180")
(command "_insert" "blkuc9" "2880,888.53" "1" "1" "0")
(command "_insert" "blkuc9" "2880,888.16" "1" "1" "180")
(command "_insert" "blkuc9" "2880,888.9" "1" "1" "0")
(command "_insert" "blkuc9" "2880,888.53" "1" "1" "180")
(command "_insert" "blkuc9" "2880,889.27" "1" "1" "0")
(command "_insert" "blkuc9" "2880,888.9" "1" "1" "180")
(command "_insert" "blkuc9" "2880,889.64" "1" "1" "0")
(command "_insert" "blkuc9" "2880,889.27" "1" "1" "180")
(command "_insert" "blkuc9" "2880,890.01" "1" "1" "0")
(command "_insert" "blkuc9" "2880,889.64" "1" "1" "180")
(command "_insert" "blkuc9" "2880,890.38" "1" "1" "0")
(command "_insert" "blkuc9" "2880,890.01" "1" "1" "180")
(command "_insert" "blkuc9" "2880,890.75" "1" "1" "0")
(command "_insert" "blkuc9" "2880,890.38" "1" "1" "180")
(command "_insert" "blkuc9" "2880,891.12" "1" "1" "0")
(command "_insert" "blkuc9" "2880,890.75" "1" "1" "180")
(command "_insert" "blkuc9" "2880,891.49" "1" "1" "0")
(command "_insert" "blkuc9" "2880,891.12" "1" "1" "180")
(command "_insert" "blkuc9" "2880,891.86" "1" "1" "0")
(command "_insert" "blkuc9" "2880,891.49" "1" "1" "180")
(command "_insert" "blkuc9" "2880,892.23" "1" "1" "0")
(command "_insert" "blkuc9" "2880,891.86" "1" "1" "180")
(command "_insert" "blkuc9" "2880,892.6" "1" "1" "0")
(command "_insert" "blkuc9" "2880,892.23" "1" "1" "180")
(command "_insert" "blkuc9" "2880,892.97" "1" "1" "0")
(command "_insert" "blkuc9" "2880,892.6" "1" "1" "180")
(command "_insert" "blkuc9" "2880,893.34" "1" "1" "0")
(command "_insert" "blkuc9" "2880,892.97" "1" "1" "180")
(command "_insert" "blkuc9" "2880,893.71" "1" "1" "0")
(command "_insert" "blkuc9" "2880,893.34" "1" "1" "180")
(command "_insert" "blkuc9" "2880,894.08" "1" "1" "0")
(command "_insert" "blkuc9" "2880,893.71" "1" "1" "180")
(command "_insert" "blkuc9" "2880,894.45" "1" "1" "0")
(command "_insert" "blkuc9" "2880,894.08" "1" "1" "180")
(command "_insert" "blkuc9" "2880,894.82" "1" "1" "0")
(command "_insert" "blkuc9" "2880,894.45" "1" "1" "180")
(command "_insert" "blkuc9" "2880,895.19" "1" "1" "0")
(command "_insert" "blkuc9" "2880,894.82" "1" "1" "180")
(command "_insert" "blkuc9" "2880,895.56" "1" "1" "0")
(command "_insert" "blkuc9" "2880,895.19" "1" "1" "180")
(command "_insert" "blkuc9" "2880,895.93" "1" "1" "0")
(command "_insert" "blkuc9" "2880,895.56" "1" "1" "180")
(command "_insert" "blkuc9" "2880,896.3" "1" "1" "0")
(command "_insert" "blkuc9" "2880,895.93" "1" "1" "180")
(command "_insert" "blkuc9" "2880,896.67" "1" "1" "0")
(command "_insert" "blkuc9" "2880,896.3" "1" "1" "180")
(command "_insert" "blkuc9" "2880,897.04" "1" "1" "0")
(command "_insert" "blkuc9" "2880,896.67" "1" "1" "180")
(command "_insert" "blkuc9" "2880,897.41" "1" "1" "0")
(command "_insert" "blkuc9" "2880,897.04" "1" "1" "180")
(command "_insert" "blkuc9" "2880,897.78" "1" "1" "0")
(command "_insert" "blkuc9" "2880,897.41" "1" "1" "180")
(command "_insert" "blkuc9" "2880,898.15" "1" "1" "0")
(command "_insert" "blkuc9" "2880,897.78" "1" "1" "180")
(command "_insert" "blkuc9" "2880,898.52" "1" "1" "0")
(command "_insert" "blkuc9" "2880,898.15" "1" "1" "180")
(command "_insert" "blkuc9" "2880,898.89" "1" "1" "0")
(command "_insert" "blkuc9" "2880,898.52" "1" "1" "180")
(command "_insert" "blkuc9" "2880,899.26" "1" "1" "0")
(command "_insert" "blkuc9" "2880,898.89" "1" "1" "180")
(command "_insert" "blkuc9" "2880,899.63" "1" "1" "0")
(command "_insert" "blkuc9" "2880,899.26" "1" "1" "180")
(command "_insert" "blkuc9" "2880,900" "1" "1" "0")
(command "_insert" "blkuc9" "2880,899.63" "1" "1" "180")
(command "_insert" "blkuc9" "2880,900.37" "1" "1" "0")
(command "_insert" "blkuc9" "2880,900" "1" "1" "180")
(command "_insert" "blkuc9" "2880,900.74" "1" "1" "0")
(command "_insert" "blkuc9" "2880,900.37" "1" "1" "180")
(command "_insert" "blkuc9" "2880,901.11" "1" "1" "0")
(command "_insert" "blkuc9" "2880,900.74" "1" "1" "180")
(command "_insert" "blkuc9" "2880,901.48" "1" "1" "0")
(command "_insert" "blkuc9" "2880,901.11" "1" "1" "180")
(command "_insert" "blkuc9" "2880,901.85" "1" "1" "0")
(command "_insert" "blkuc9" "2880,901.48" "1" "1" "180")
(command "_insert" "blkuc9" "2880,902.22" "1" "1" "0")
(command "_insert" "blkuc9" "2880,901.85" "1" "1" "180")
(command "_insert" "blkuc9" "2880,902.59" "1" "1" "0")
(command "_insert" "blkuc9" "2880,902.22" "1" "1" "180")
(command "_insert" "blkuc9" "2880,902.96" "1" "1" "0")
(command "_insert" "blkuc9" "2880,902.59" "1" "1" "180")
(command "_insert" "blkuc9" "2880,903.33" "1" "1" "0")
(command "_insert" "blkuc9" "2880,902.96" "1" "1" "180")
(command "_insert" "blkuc9" "2880,903.7" "1" "1" "0")
(command "_insert" "blkuc9" "2880,903.33" "1" "1" "180")
(command "_insert" "blkuc9" "2880,904.07" "1" "1" "0")
(command "_insert" "blkuc9" "2880,903.7" "1" "1" "180")
(command "_insert" "blkuc9" "2880,904.44" "1" "1" "0")
(command "_insert" "blkuc9" "2880,904.07" "1" "1" "180")
(command "_insert" "blkuc9" "2880,904.81" "1" "1" "0")
(command "_insert" "blkuc9" "2880,904.44" "1" "1" "180")
(command "_insert" "blkuc9" "2880,905.18" "1" "1" "0")
(command "_insert" "blkuc9" "2880,904.81" "1" "1" "180")
(command "_insert" "blkuc9" "2880,905.55" "1" "1" "0")
(command "_insert" "blkuc9" "2880,905.18" "1" "1" "180")
(command "_insert" "blkuc9" "2880,905.92" "1" "1" "0")
(command "_insert" "blkuc9" "2880,905.55" "1" "1" "180")
(command "_insert" "blkuc9" "2880,906.29" "1" "1" "0")
(command "_insert" "blkuc9" "2880,905.92" "1" "1" "180")
(command "_insert" "blkuc9" "2880,906.66" "1" "1" "0")
(command "_insert" "blkuc9" "2880,906.29" "1" "1" "180")
(command "_insert" "blkuc9" "2880,907.03" "1" "1" "0")
(command "_insert" "blkuc9" "2880,906.66" "1" "1" "180")
(command "_insert" "blkuc9" "2880,907.4" "1" "1" "0")
(command "_insert" "blkuc9" "2880,907.03" "1" "1" "180")
(command "_insert" "blkuc9" "2880,907.77" "1" "1" "0")
(command "_insert" "blkuc9" "2880,907.4" "1" "1" "180")
(command "_insert" "blkuc9" "2880,908.14" "1" "1" "0")
(command "_insert" "blkuc9" "2880,907.77" "1" "1" "180")
(command "_insert" "blkuc9" "2880,908.51" "1" "1" "0")
(command "_insert" "blkuc9" "2880,908.14" "1" "1" "180")
(command "_insert" "blkuc9" "2880,908.88" "1" "1" "0")
(command "_insert" "blkuc9" "2880,908.51" "1" "1" "180")
(command "_insert" "blkuc9" "2880,909.25" "1" "1" "0")
(command "_insert" "blkuc9" "2880,908.88" "1" "1" "180")
(command "_insert" "blkuc9" "2880,909.62" "1" "1" "0")
(command "_insert" "blkuc9" "2880,909.25" "1" "1" "180")
(command "_insert" "blkuc9" "2880,909.99" "1" "1" "0")
(command "_insert" "blkuc9" "2880,909.62" "1" "1" "180")
(command "_insert" "blkuc9" "2880,910.36" "1" "1" "0")
(command "_insert" "blkuc9" "2880,909.99" "1" "1" "180")
(command "_insert" "blkuc9" "2880,910.73" "1" "1" "0")
(command "_insert" "blkuc9" "2880,910.36" "1" "1" "180")
(command "_insert" "blkuc9" "2880,911.1" "1" "1" "0")
(command "_insert" "blkuc9" "2880,910.73" "1" "1" "180")
(command "_insert" "blkuc9" "2880,911.47" "1" "1" "0")
(command "_insert" "blkuc9" "2880,911.1" "1" "1" "180")
(command "_insert" "blkuc9" "2880,911.84" "1" "1" "0")
(command "_insert" "blkuc9" "2880,911.47" "1" "1" "180")
(command "_insert" "blkuc9" "2880,912.21" "1" "1" "0")
(command "_insert" "blkuc9" "2880,911.84" "1" "1" "180")
(command "_insert" "blkuc9" "2880,912.58" "1" "1" "0")
(command "_insert" "blkuc9" "2880,912.21" "1" "1" "180")
(command "_insert" "blkuc9" "2880,912.95" "1" "1" "0")
(command "_insert" "blkuc9" "2880,912.58" "1" "1" "180")
(command "_insert" "blkuc9" "2880,913.32" "1" "1" "0")
(command "_insert" "blkuc9" "2880,912.95" "1" "1" "180")
(command "_insert" "blkuc9" "2880,913.69" "1" "1" "0")
(command "_insert" "blkuc9" "2880,913.32" "1" "1" "180")
(command "_insert" "blkuc9" "2880,914.06" "1" "1" "0")
(command "_insert" "blkuc9" "2880,913.69" "1" "1" "180")
(command "_insert" "blkuc9" "2880,914.43" "1" "1" "0")
(command "_insert" "blkuc9" "2880,914.06" "1" "1" "180")
(command "_insert" "blkuc9" "2880,914.8" "1" "1" "0")
(command "_insert" "blkuc9" "2880,914.43" "1" "1" "180")
(command "_insert" "blkuc9" "2880,915.17" "1" "1" "0")
(command "_insert" "blkuc9" "2880,914.8" "1" "1" "180")
(command "_insert" "blkuc9" "2880,915.54" "1" "1" "0")
(command "_insert" "blkuc9" "2880,915.17" "1" "1" "180")
(command "_insert" "blkuc9" "2880,915.91" "1" "1" "0")
(command "_insert" "blkuc9" "2880,915.54" "1" "1" "180")
(command "_insert" "blkuc9" "2880,916.28" "1" "1" "0")
(command "_insert" "blkuc9" "2880,915.91" "1" "1" "180")
(command "_insert" "blkuc9" "2880,916.65" "1" "1" "0")
(command "_insert" "blkuc9" "2880,916.28" "1" "1" "180")
(command "_insert" "blkuc9" "2880,917.02" "1" "1" "0")
(command "_insert" "blkuc9" "2880,916.65" "1" "1" "180")
(command "_insert" "blkuc9" "2880,917.39" "1" "1" "0")
(command "_insert" "blkuc9" "2880,917.02" "1" "1" "180")
(command "_insert" "blkuc9" "2880,917.76" "1" "1" "0")
(command "_insert" "blkuc9" "2880,917.39" "1" "1" "180")
(command "_insert" "blkuc9" "2880,918.13" "1" "1" "0")
(command "_insert" "blkuc9" "2880,917.76" "1" "1" "180")
(command "_insert" "blkuc9" "2880,918.5" "1" "1" "0")
(command "_insert" "blkuc9" "2880,918.13" "1" "1" "180")
(command "_insert" "blkuc9" "2880,918.87" "1" "1" "0")
(command "_insert" "blkuc9" "2880,918.5" "1" "1" "180")
(command "_insert" "blkuc9" "2880,919.24" "1" "1" "0")
(command "_insert" "blkuc9" "2880,918.87" "1" "1" "180")
(command "_insert" "blkuc9" "2880,919.61" "1" "1" "0")
(command "_insert" "blkuc9" "2880,919.24" "1" "1" "180")
(command "_insert" "blkuc9" "2880,919.98" "1" "1" "0")
(command "_insert" "blkuc9" "2880,919.61" "1" "1" "180")
(command "_insert" "blkuc9" "2880,920.35" "1" "1" "0")
(command "_insert" "blkuc9" "2880,919.98" "1" "1" "180")
(command "_insert" "blkuc9" "2880,920.72" "1" "1" "0")
(command "_insert" "blkuc9" "2880,920.35" "1" "1" "180")
(command "_insert" "blkuc9" "2880,921.09" "1" "1" "0")
(command "_insert" "blkuc9" "2880,920.72" "1" "1" "180")
(command "_insert" "blkuc9" "2880,921.46" "1" "1" "0")
(command "_insert" "blkuc9" "2880,921.09" "1" "1" "180")
(command "_insert" "blkuc9" "2880,921.83" "1" "1" "0")
(command "_insert" "blkuc9" "2880,921.46" "1" "1" "180")
(command "_insert" "blkuc9" "2880,922.2" "1" "1" "0")
(command "_insert" "blkuc9" "2880,921.83" "1" "1" "180")
(command "_insert" "blkuc9" "2880,922.57" "1" "1" "0")
(command "_insert" "blkuc9" "2880,922.2" "1" "1" "180")
(command "_insert" "blkuc9" "2880,922.94" "1" "1" "0")
(command "_insert" "blkuc9" "2880,922.57" "1" "1" "180")
(command "_insert" "blkuc9" "2880,923.31" "1" "1" "0")
(command "_insert" "blkuc9" "2880,922.94" "1" "1" "180")
(command "_insert" "blkuc9" "2880,923.68" "1" "1" "0")
(command "_insert" "blkuc9" "2880,923.31" "1" "1" "180")
(command "_insert" "blkuc9" "2880,924.05" "1" "1" "0")
(command "_insert" "blkuc9" "2880,923.68" "1" "1" "180")
(command "_insert" "blkuc9" "2880,924.42" "1" "1" "0")
(command "_insert" "blkuc9" "2880,924.05" "1" "1" "180")
(command "_insert" "blkuc9" "2880,924.79" "1" "1" "0")
(command "_insert" "blkuc9" "2880,924.42" "1" "1" "180")
(command "_insert" "blkuc9" "2880,925.16" "1" "1" "0")
(command "_insert" "blkuc9" "2880,924.79" "1" "1" "180")
(command "_insert" "blkuc9" "2880,925.53" "1" "1" "0")
(command "_insert" "blkuc9" "2880,925.16" "1" "1" "180")
(command "_insert" "blkuc9" "2880,925.9" "1" "1" "0")
(command "_insert" "blkuc9" "2880,925.53" "1" "1" "180")
(command "_insert" "blkuc9" "2880,926.27" "1" "1" "0")
(command "_insert" "blkuc9" "2880,925.9" "1" "1" "180")
(command "_insert" "blkuc9" "2880,926.64" "1" "1" "0")
(command "_insert" "blkuc9" "2880,926.27" "1" "1" "180")
(command "_insert" "blkuc9" "2880,927.01" "1" "1" "0")
(command "_insert" "blkuc9" "2880,926.64" "1" "1" "180")
(command "_insert" "blkuc9" "2880,927.38" "1" "1" "0")
(command "_insert" "blkuc9" "2880,927.01" "1" "1" "180")
(command "_insert" "blkuc9" "2880,927.75" "1" "1" "0")
(command "_insert" "blkuc9" "2880,927.38" "1" "1" "180")
(command "_layer" "set" "phccover" "")
(command "_rectangle" "2878.87,933.3" "2881.13,866.7")
(command "_layer" "set" "nitride" "")
(setq phc9 currobj)
(command "_layer" "set" "cover" "")
(command "_rectangle" "2878.87,836.7" "2881.13,963.3")
(command "_layer" "set" "nitride" "")
(command "_layer" "set" "text" "")
(command "_circle" "2877.92,846.7" "0.075")
(command "_circle" "2877.545,846.7" "0.15")
(command "_circle" "2877.17,846.7" "0.075")
(command "_circle" "2876.795,846.7" "0.15")
(command "_circle" "2877.92,848.7" "0.075")
(command "_circle" "2877.545,848.7" "0.075")
(command "_circle" "2877.17,848.7" "0.15")
(command "_circle" "2876.795,848.7" "0.15")
(command "_circle" "2877.92,850.7" "0.075")
(command "_circle" "2877.545,850.7" "0.15")
(command "_circle" "2877.17,850.7" "0.15")
(command "_circle" "2876.795,850.7" "0.15")
(command "_circle" "2877.92,852.7" "0.075")
(command "_circle" "2877.545,852.7" "0.075")
(command "_circle" "2877.17,852.7" "0.075")
(command "_circle" "2876.795,852.7" "0.075")
(command "_circle" "2876.42,852.7" "0.15")
(command "_circle" "2877.92,854.7" "0.075")
(command "_circle" "2877.545,854.7" "0.15")
(command "_circle" "2877.17,854.7" "0.075")
(command "_circle" "2876.795,854.7" "0.075")
(command "_circle" "2876.42,854.7" "0.15")
(command "_circle" "2877.92,856.7" "0.075")
(command "_circle" "2877.545,856.7" "0.075")
(command "_circle" "2877.17,856.7" "0.15")
(command "_circle" "2876.795,856.7" "0.075")
(command "_circle" "2876.42,856.7" "0.15")
(command "_circle" "2877.92,858.7" "0.075")
(command "_circle" "2877.545,858.7" "0.15")
(command "_circle" "2877.17,858.7" "0.15")
(command "_circle" "2876.795,858.7" "0.075")
(command "_circle" "2876.42,858.7" "0.15")
(command "_circle" "2877.92,860.7" "0.075")
(command "_circle" "2877.545,860.7" "0.075")
(command "_circle" "2877.17,860.7" "0.075")
(command "_circle" "2876.795,860.7" "0.15")
(command "_circle" "2876.42,860.7" "0.15")
(command "_circle" "2877.92,862.7" "0.075")
(command "_circle" "2877.545,862.7" "0.15")
(command "_circle" "2877.17,862.7" "0.075")
(command "_circle" "2876.795,862.7" "0.15")
(command "_circle" "2876.42,862.7" "0.15")
(command "_circle" "2877.92,864.7" "0.075")
(command "_circle" "2877.545,864.7" "0.075")
(command "_circle" "2877.17,864.7" "0.15")
(command "_circle" "2876.795,864.7" "0.15")
(command "_circle" "2876.42,864.7" "0.15")
(command "_circle" "2877.92,866.7" "0.075")
(command "_circle" "2877.545,866.7" "0.15")
(command "_circle" "2877.17,866.7" "0.15")
(command "_circle" "2876.795,866.7" "0.15")
(command "_circle" "2876.42,866.7" "0.15")
(command "_circle" "2877.92,868.7" "0.075")
(command "_circle" "2877.545,868.7" "0.075")
(command "_circle" "2877.17,868.7" "0.075")
(command "_circle" "2876.795,868.7" "0.075")
(command "_circle" "2876.42,868.7" "0.075")
(command "_circle" "2876.045,868.7" "0.15")
(command "_circle" "2877.92,870.7" "0.075")
(command "_circle" "2877.545,870.7" "0.15")
(command "_circle" "2877.17,870.7" "0.075")
(command "_circle" "2876.795,870.7" "0.075")
(command "_circle" "2876.42,870.7" "0.075")
(command "_circle" "2876.045,870.7" "0.15")
(command "_circle" "2877.92,872.7" "0.075")
(command "_circle" "2877.545,872.7" "0.075")
(command "_circle" "2877.17,872.7" "0.15")
(command "_circle" "2876.795,872.7" "0.075")
(command "_circle" "2876.42,872.7" "0.075")
(command "_circle" "2876.045,872.7" "0.15")
(command "_circle" "2877.92,874.7" "0.075")
(command "_circle" "2877.545,874.7" "0.15")
(command "_circle" "2877.17,874.7" "0.15")
(command "_circle" "2876.795,874.7" "0.075")
(command "_circle" "2876.42,874.7" "0.075")
(command "_circle" "2876.045,874.7" "0.15")
(command "_circle" "2877.92,876.7" "0.075")
(command "_circle" "2877.545,876.7" "0.075")
(command "_circle" "2877.17,876.7" "0.075")
(command "_circle" "2876.795,876.7" "0.15")
(command "_circle" "2876.42,876.7" "0.075")
(command "_circle" "2876.045,876.7" "0.15")
(command "_circle" "2877.92,878.7" "0.075")
(command "_circle" "2877.545,878.7" "0.15")
(command "_circle" "2877.17,878.7" "0.075")
(command "_circle" "2876.795,878.7" "0.15")
(command "_circle" "2876.42,878.7" "0.075")
(command "_circle" "2876.045,878.7" "0.15")
(command "_circle" "2877.92,880.7" "0.075")
(command "_circle" "2877.545,880.7" "0.075")
(command "_circle" "2877.17,880.7" "0.15")
(command "_circle" "2876.795,880.7" "0.15")
(command "_circle" "2876.42,880.7" "0.075")
(command "_circle" "2876.045,880.7" "0.15")
(command "_circle" "2877.92,882.7" "0.075")
(command "_circle" "2877.545,882.7" "0.15")
(command "_circle" "2877.17,882.7" "0.15")
(command "_circle" "2876.795,882.7" "0.15")
(command "_circle" "2876.42,882.7" "0.075")
(command "_circle" "2876.045,882.7" "0.15")
(command "_circle" "2877.92,884.7" "0.075")
(command "_circle" "2877.545,884.7" "0.075")
(command "_circle" "2877.17,884.7" "0.075")
(command "_circle" "2876.795,884.7" "0.075")
(command "_circle" "2876.42,884.7" "0.15")
(command "_circle" "2876.045,884.7" "0.15")
(command "_circle" "2877.92,886.7" "0.075")
(command "_circle" "2877.545,886.7" "0.15")
(command "_circle" "2877.17,886.7" "0.075")
(command "_circle" "2876.795,886.7" "0.075")
(command "_circle" "2876.42,886.7" "0.15")
(command "_circle" "2876.045,886.7" "0.15")
(command "_circle" "2877.92,888.7" "0.075")
(command "_circle" "2877.545,888.7" "0.075")
(command "_circle" "2877.17,888.7" "0.15")
(command "_circle" "2876.795,888.7" "0.075")
(command "_circle" "2876.42,888.7" "0.15")
(command "_circle" "2876.045,888.7" "0.15")
(command "_circle" "2877.92,890.7" "0.075")
(command "_circle" "2877.545,890.7" "0.15")
(command "_circle" "2877.17,890.7" "0.15")
(command "_circle" "2876.795,890.7" "0.075")
(command "_circle" "2876.42,890.7" "0.15")
(command "_circle" "2876.045,890.7" "0.15")
(command "_circle" "2877.92,892.7" "0.075")
(command "_circle" "2877.545,892.7" "0.075")
(command "_circle" "2877.17,892.7" "0.075")
(command "_circle" "2876.795,892.7" "0.15")
(command "_circle" "2876.42,892.7" "0.15")
(command "_circle" "2876.045,892.7" "0.15")
(command "_circle" "2877.92,894.7" "0.075")
(command "_circle" "2877.545,894.7" "0.15")
(command "_circle" "2877.17,894.7" "0.075")
(command "_circle" "2876.795,894.7" "0.15")
(command "_circle" "2876.42,894.7" "0.15")
(command "_circle" "2876.045,894.7" "0.15")
(command "_circle" "2877.92,896.7" "0.075")
(command "_circle" "2877.545,896.7" "0.075")
(command "_circle" "2877.17,896.7" "0.15")
(command "_circle" "2876.795,896.7" "0.15")
(command "_circle" "2876.42,896.7" "0.15")
(command "_circle" "2876.045,896.7" "0.15")
(command "_circle" "2877.92,898.7" "0.075")
(command "_circle" "2877.545,898.7" "0.15")
(command "_circle" "2877.17,898.7" "0.15")
(command "_circle" "2876.795,898.7" "0.15")
(command "_circle" "2876.42,898.7" "0.15")
(command "_circle" "2876.045,898.7" "0.15")
(command "_circle" "2877.92,900.7" "0.075")
(command "_circle" "2877.545,900.7" "0.075")
(command "_circle" "2877.17,900.7" "0.075")
(command "_circle" "2876.795,900.7" "0.075")
(command "_circle" "2876.42,900.7" "0.075")
(command "_circle" "2876.045,900.7" "0.075")
(command "_circle" "2875.67,900.7" "0.15")
(command "_circle" "2877.92,902.7" "0.075")
(command "_circle" "2877.545,902.7" "0.15")
(command "_circle" "2877.17,902.7" "0.075")
(command "_circle" "2876.795,902.7" "0.075")
(command "_circle" "2876.42,902.7" "0.075")
(command "_circle" "2876.045,902.7" "0.075")
(command "_circle" "2875.67,902.7" "0.15")
(command "_circle" "2877.92,904.7" "0.075")
(command "_circle" "2877.545,904.7" "0.075")
(command "_circle" "2877.17,904.7" "0.15")
(command "_circle" "2876.795,904.7" "0.075")
(command "_circle" "2876.42,904.7" "0.075")
(command "_circle" "2876.045,904.7" "0.075")
(command "_circle" "2875.67,904.7" "0.15")
(command "_circle" "2877.92,906.7" "0.075")
(command "_circle" "2877.545,906.7" "0.15")
(command "_circle" "2877.17,906.7" "0.15")
(command "_circle" "2876.795,906.7" "0.075")
(command "_circle" "2876.42,906.7" "0.075")
(command "_circle" "2876.045,906.7" "0.075")
(command "_circle" "2875.67,906.7" "0.15")
(command "_circle" "2877.92,908.7" "0.075")
(command "_circle" "2877.545,908.7" "0.075")
(command "_circle" "2877.17,908.7" "0.075")
(command "_circle" "2876.795,908.7" "0.15")
(command "_circle" "2876.42,908.7" "0.075")
(command "_circle" "2876.045,908.7" "0.075")
(command "_circle" "2875.67,908.7" "0.15")
(command "_circle" "2877.92,910.7" "0.075")
(command "_circle" "2877.545,910.7" "0.15")
(command "_circle" "2877.17,910.7" "0.075")
(command "_circle" "2876.795,910.7" "0.15")
(command "_circle" "2876.42,910.7" "0.075")
(command "_circle" "2876.045,910.7" "0.075")
(command "_circle" "2875.67,910.7" "0.15")
(command "_circle" "2877.92,912.7" "0.075")
(command "_circle" "2877.545,912.7" "0.075")
(command "_circle" "2877.17,912.7" "0.15")
(command "_circle" "2876.795,912.7" "0.15")
(command "_circle" "2876.42,912.7" "0.075")
(command "_circle" "2876.045,912.7" "0.075")
(command "_circle" "2875.67,912.7" "0.15")
(command "_circle" "2877.92,914.7" "0.075")
(command "_circle" "2877.545,914.7" "0.15")
(command "_circle" "2877.17,914.7" "0.15")
(command "_circle" "2876.795,914.7" "0.15")
(command "_circle" "2876.42,914.7" "0.075")
(command "_circle" "2876.045,914.7" "0.075")
(command "_circle" "2875.67,914.7" "0.15")
(command "_circle" "2877.92,916.7" "0.075")
(command "_circle" "2877.545,916.7" "0.075")
(command "_circle" "2877.17,916.7" "0.075")
(command "_circle" "2876.795,916.7" "0.075")
(command "_circle" "2876.42,916.7" "0.15")
(command "_circle" "2876.045,916.7" "0.075")
(command "_circle" "2875.67,916.7" "0.15")
(command "_circle" "2877.92,918.7" "0.075")
(command "_circle" "2877.545,918.7" "0.15")
(command "_circle" "2877.17,918.7" "0.075")
(command "_circle" "2876.795,918.7" "0.075")
(command "_circle" "2876.42,918.7" "0.15")
(command "_circle" "2876.045,918.7" "0.075")
(command "_circle" "2875.67,918.7" "0.15")
(command "_circle" "2877.92,920.7" "0.075")
(command "_circle" "2877.545,920.7" "0.075")
(command "_circle" "2877.17,920.7" "0.15")
(command "_circle" "2876.795,920.7" "0.075")
(command "_circle" "2876.42,920.7" "0.15")
(command "_circle" "2876.045,920.7" "0.075")
(command "_circle" "2875.67,920.7" "0.15")
(command "_circle" "2877.92,922.7" "0.075")
(command "_circle" "2877.545,922.7" "0.15")
(command "_circle" "2877.17,922.7" "0.15")
(command "_circle" "2876.795,922.7" "0.075")
(command "_circle" "2876.42,922.7" "0.15")
(command "_circle" "2876.045,922.7" "0.075")
(command "_circle" "2875.67,922.7" "0.15")
(command "_circle" "2877.92,924.7" "0.075")
(command "_circle" "2877.545,924.7" "0.075")
(command "_circle" "2877.17,924.7" "0.075")
(command "_circle" "2876.795,924.7" "0.15")
(command "_circle" "2876.42,924.7" "0.15")
(command "_circle" "2876.045,924.7" "0.075")
(command "_circle" "2875.67,924.7" "0.15")
(command "_circle" "2877.92,926.7" "0.075")
(command "_circle" "2877.545,926.7" "0.15")
(command "_circle" "2877.17,926.7" "0.075")
(command "_circle" "2876.795,926.7" "0.15")
(command "_circle" "2876.42,926.7" "0.15")
(command "_circle" "2876.045,926.7" "0.075")
(command "_circle" "2875.67,926.7" "0.15")
(command "_circle" "2877.92,928.7" "0.075")
(command "_circle" "2877.545,928.7" "0.075")
(command "_circle" "2877.17,928.7" "0.15")
(command "_circle" "2876.795,928.7" "0.15")
(command "_circle" "2876.42,928.7" "0.15")
(command "_circle" "2876.045,928.7" "0.075")
(command "_circle" "2875.67,928.7" "0.15")
(command "_circle" "2877.92,930.7" "0.075")
(command "_circle" "2877.545,930.7" "0.15")
(command "_circle" "2877.17,930.7" "0.15")
(command "_circle" "2876.795,930.7" "0.15")
(command "_circle" "2876.42,930.7" "0.15")
(command "_circle" "2876.045,930.7" "0.075")
(command "_circle" "2875.67,930.7" "0.15")
(command "_circle" "2877.92,932.7" "0.075")
(command "_circle" "2877.545,932.7" "0.075")
(command "_circle" "2877.17,932.7" "0.075")
(command "_circle" "2876.795,932.7" "0.075")
(command "_circle" "2876.42,932.7" "0.075")
(command "_circle" "2876.045,932.7" "0.15")
(command "_circle" "2875.67,932.7" "0.15")
(command "_circle" "2877.92,934.7" "0.075")
(command "_circle" "2877.545,934.7" "0.15")
(command "_circle" "2877.17,934.7" "0.075")
(command "_circle" "2876.795,934.7" "0.075")
(command "_circle" "2876.42,934.7" "0.075")
(command "_circle" "2876.045,934.7" "0.15")
(command "_circle" "2875.67,934.7" "0.15")
(command "_circle" "2877.92,936.7" "0.075")
(command "_circle" "2877.545,936.7" "0.075")
(command "_circle" "2877.17,936.7" "0.15")
(command "_circle" "2876.795,936.7" "0.075")
(command "_circle" "2876.42,936.7" "0.075")
(command "_circle" "2876.045,936.7" "0.15")
(command "_circle" "2875.67,936.7" "0.15")
(command "_circle" "2877.92,938.7" "0.075")
(command "_circle" "2877.545,938.7" "0.15")
(command "_circle" "2877.17,938.7" "0.15")
(command "_circle" "2876.795,938.7" "0.075")
(command "_circle" "2876.42,938.7" "0.075")
(command "_circle" "2876.045,938.7" "0.15")
(command "_circle" "2875.67,938.7" "0.15")
(command "_circle" "2877.92,940.7" "0.075")
(command "_circle" "2877.545,940.7" "0.075")
(command "_circle" "2877.17,940.7" "0.075")
(command "_circle" "2876.795,940.7" "0.15")
(command "_circle" "2876.42,940.7" "0.075")
(command "_circle" "2876.045,940.7" "0.15")
(command "_circle" "2875.67,940.7" "0.15")
(command "_circle" "2877.92,942.7" "0.075")
(command "_circle" "2877.545,942.7" "0.15")
(command "_circle" "2877.17,942.7" "0.075")
(command "_circle" "2876.795,942.7" "0.15")
(command "_circle" "2876.42,942.7" "0.075")
(command "_circle" "2876.045,942.7" "0.15")
(command "_circle" "2875.67,942.7" "0.15")
(command "_circle" "2877.92,944.7" "0.075")
(command "_circle" "2877.545,944.7" "0.075")
(command "_circle" "2877.17,944.7" "0.15")
(command "_circle" "2876.795,944.7" "0.15")
(command "_circle" "2876.42,944.7" "0.075")
(command "_circle" "2876.045,944.7" "0.15")
(command "_circle" "2875.67,944.7" "0.15")
(command "_circle" "2877.92,946.7" "0.075")
(command "_circle" "2877.545,946.7" "0.15")
(command "_circle" "2877.17,946.7" "0.15")
(command "_circle" "2876.795,946.7" "0.15")
(command "_circle" "2876.42,946.7" "0.075")
(command "_circle" "2876.045,946.7" "0.15")
(command "_circle" "2875.67,946.7" "0.15")
(command "_circle" "2877.92,948.7" "0.075")
(command "_circle" "2877.545,948.7" "0.075")
(command "_circle" "2877.17,948.7" "0.075")
(command "_circle" "2876.795,948.7" "0.075")
(command "_circle" "2876.42,948.7" "0.15")
(command "_circle" "2876.045,948.7" "0.15")
(command "_circle" "2875.67,948.7" "0.15")
(command "_circle" "2877.92,950.7" "0.075")
(command "_circle" "2877.545,950.7" "0.15")
(command "_circle" "2877.17,950.7" "0.075")
(command "_circle" "2876.795,950.7" "0.075")
(command "_circle" "2876.42,950.7" "0.15")
(command "_circle" "2876.045,950.7" "0.15")
(command "_circle" "2875.67,950.7" "0.15")
(command "_circle" "2877.92,952.7" "0.075")
(command "_circle" "2877.545,952.7" "0.075")
(command "_circle" "2877.17,952.7" "0.15")
(command "_circle" "2876.795,952.7" "0.075")
(command "_circle" "2876.42,952.7" "0.15")
(command "_circle" "2876.045,952.7" "0.15")
(command "_circle" "2875.67,952.7" "0.15")
(command "_circle" "2877.92,954.7" "0.075")
(command "_circle" "2877.545,954.7" "0.15")
(command "_circle" "2877.17,954.7" "0.15")
(command "_circle" "2876.795,954.7" "0.075")
(command "_circle" "2876.42,954.7" "0.15")
(command "_circle" "2876.045,954.7" "0.15")
(command "_circle" "2875.67,954.7" "0.15")
(command "_circle" "2877.92,956.7" "0.075")
(command "_circle" "2877.545,956.7" "0.075")
(command "_circle" "2877.17,956.7" "0.075")
(command "_circle" "2876.795,956.7" "0.15")
(command "_circle" "2876.42,956.7" "0.15")
(command "_circle" "2876.045,956.7" "0.15")
(command "_circle" "2875.67,956.7" "0.15")
(command "_circle" "2877.92,958.7" "0.075")
(command "_circle" "2877.545,958.7" "0.15")
(command "_circle" "2877.17,958.7" "0.075")
(command "_circle" "2876.795,958.7" "0.15")
(command "_circle" "2876.42,958.7" "0.15")
(command "_circle" "2876.045,958.7" "0.15")
(command "_circle" "2875.67,958.7" "0.15")
(command "_circle" "2877.92,960.7" "0.075")
(command "_circle" "2877.545,960.7" "0.075")
(command "_circle" "2877.17,960.7" "0.15")
(command "_circle" "2876.795,960.7" "0.15")
(command "_circle" "2876.42,960.7" "0.15")
(command "_circle" "2876.045,960.7" "0.15")
(command "_circle" "2875.67,960.7" "0.15")
(command "_circle" "2877.92,962.7" "0.075")
(command "_circle" "2877.545,962.7" "0.15")
(command "_circle" "2877.17,962.7" "0.15")
(command "_circle" "2876.795,962.7" "0.15")
(command "_circle" "2876.42,962.7" "0.15")
(command "_circle" "2876.045,962.7" "0.15")
(command "_circle" "2875.67,962.7" "0.15")
(command "_layer" "set" "nitride" "")
(command "_layer" "set" "text" "")
(command-s "_text" "2866.87,963.3" "2" "-90" "a = 370 nm" )
(sssetfirst nil (ssget "_L"))
(if (not (numberp (vl-string-search "Mac" (getvar "platform")))) (c:txtexp))
(command "_layer" "set" "nitride" "")
(command "_layer" "set" "text" "")
(command-s "_text" "2863.87,963.3" "2" "-90" "gap = 270 nm" )
(sssetfirst nil (ssget "_L"))
(if (not (numberp (vl-string-search "Mac" (getvar "platform")))) (c:txtexp))
(command "_layer" "set" "nitride" "")
(command "_layer" "set" "text" "")
(command-s "_text" "2860.87,963.3" "2" "-90" "amplitude = 134 nm" )
(sssetfirst nil (ssget "_L"))
(if (not (numberp (vl-string-search "Mac" (getvar "platform")))) (c:txtexp))
(command "_layer" "set" "nitride" "")
(command "_layer" "set" "text" "")
(command-s "_text" "2857.87,963.3" "2" "-90" "start width = 280 nm" )
(sssetfirst nil (ssget "_L"))
(if (not (numberp (vl-string-search "Mac" (getvar "platform")))) (c:txtexp))
(command "_layer" "set" "nitride" "")
(command "_layer" "set" "text" "")
(command-s "_text" "2854.87,963.3" "2" "-90" "width = 296 nm" )
(sssetfirst nil (ssget "_L"))
(if (not (numberp (vl-string-search "Mac" (getvar "platform")))) (c:txtexp))
(command "_layer" "set" "nitride" "")
(command "_layer" "set" "text" "")
(command-s "_text" "2851.87,963.3" "2" "-90" "taper: 15" )
(sssetfirst nil (ssget "_L"))
(if (not (numberp (vl-string-search "Mac" (getvar "platform")))) (c:txtexp))
(command "_layer" "set" "nitride" "")
(command "_layer" "set" "text" "")
(command-s "_text" "2848.87,963.3" "2" "-90" "nominal: 150" )
(sssetfirst nil (ssget "_L"))
(if (not (numberp (vl-string-search "Mac" (getvar "platform")))) (c:txtexp))
(command "_layer" "set" "nitride" "")
(command "_layer" "set" "indicators" "")
(setq coords (list 
(list 2800.415 940) 
(list 2800.415 920) 
(list 2780.415 900) 
(list 2800.415 880) 
(list 2800.415 860) 
(list 2800.415 900) 
(list 2800.415 887.0711) 
(list 2787.4861 900) 
(list 2800.415 912.9289) 
(list 2800.415 900)))
(apply 'command (append '("pline") coords '("c")))
(command "._fillet" "radius" "1" "._fillet" "P" (entlast))
(setq coords (list 
(list 2959.585 940) 
(list 2959.585 920) 
(list 2979.585 900) 
(list 2959.585 880) 
(list 2959.585 860) 
(list 2959.585 900) 
(list 2959.585 887.0711) 
(list 2972.5139 900) 
(list 2959.585 912.9289) 
(list 2959.585 900)))
(apply 'command (append '("pline") coords '("c")))
(command "._fillet" "radius" "1" "._fillet" "P" (entlast))
(command "_layer" "set" "holes" "")
(command "_circle" "2798.0629,914.1124" "0.5")
(command "_circle" "2795.7109,911.7603" "0.5")
(command "_circle" "2793.3588,909.4083" "0.5")
(command "_circle" "2791.0067,907.0562" "0.5")
(command "_circle" "2788.6547,904.7041" "0.5")
(command "_circle" "2786.3026,902.3521" "0.5")
(command "_circle" "2783.9505,900" "0.5")
(command "_circle" "2786.3026,897.6479" "0.5")
(command "_circle" "2788.6547,895.2959" "0.5")
(command "_circle" "2791.0067,892.9438" "0.5")
(command "_circle" "2793.3588,890.5917" "0.5")
(command "_circle" "2795.7109,888.2397" "0.5")
(command "_circle" "2798.0629,885.8876" "0.5")
(command "_circle" "2961.9371,914.1124" "0.5")
(command "_circle" "2964.2891,911.7603" "0.5")
(command "_circle" "2966.6412,909.4083" "0.5")
(command "_circle" "2968.9933,907.0562" "0.5")
(command "_circle" "2971.3453,904.7041" "0.5")
(command "_circle" "2973.6974,902.3521" "0.5")
(command "_circle" "2976.0495,900" "0.5")
(command "_circle" "2973.6974,897.6479" "0.5")
(command "_circle" "2971.3453,895.2959" "0.5")
(command "_circle" "2968.9933,892.9438" "0.5")
(command "_circle" "2966.6412,890.5917" "0.5")
(command "_circle" "2964.2891,888.2397" "0.5")
(command "_circle" "2961.9371,885.8876" "0.5")
(command "_layer" "set" "nitride" "")
(command "_block" "blkcoupler9" "2880,900" coupler9 "")
(command "_insert" "blkcoupler9" "2880,900" "1" "1" "0")
(command "_insert" "blkcoupler9" "2880,900" "1" "1" "180")
(command "_block" "blksinglenanobeam9" "2880,900" singlenanobeam9 "")
(command "_insert" "blksinglenanobeam9" "2880,900" "1" "1" "0")
(command "_insert" "blksinglenanobeam9" "2880,900" "1" "1" "180")
(command "_block" "blkanglednodearray9" "2880,900" anglednodearray9 "")
(command "_insert" "blkanglednodearray9" "2880,900" "1" "1" "0")
(command "_insert" "blkanglednodearray9" "2880,900" "1" "1" "180")
(command "_block" "blkcooledsinglenanobeam9" "2880,900" cooledsinglenanobeam9 "")
(command "_insert" "blkcooledsinglenanobeam9" "2880,900" "1" "1" "0")
(command "_insert" "blkcooledsinglenanobeam9" "2880,900" "1" "1" "180")
(command "_block" "blkyjunction9" "2880,900" yjunction9 "")
(command "_insert" "blkyjunction9" "2880,900" "1" "1" "0")
(command "_insert" "blkyjunction9" "2880,900" "1" "1" "180")
; DRAWING BULGING VEE GROOVE
(command "_layer" "set" "vgroove" "")
(setq coords (list 
(list 2805.415 -605) 
(list 2805.415 0) 
(list 2805.415 0) 
(list 2805.415 1800) 
(list 2805.415 1800) 
(list 2805.415 2405) 
(list 2954.585 2405) 
(list 2954.585 1800) 
(list 2954.585 1800) 
(list 2954.585 0) 
(list 2954.585 0) 
(list 2954.585 -605)))
(apply 'command (append '("pline") coords '("c")))
(command "._fillet" "radius" "0" "._fillet" "P" (entlast))
(command "_layer" "set" "window" "")
(command "_rectangle" "2805.415,-1935" "2954.585,-600")
(command "_rectangle" "2805.415,2400" "2954.585,5300")
(command "_layer" "set" "grid" "")
(command "_rectangle" "2806.415,-1934" "2829.9433,-1909.2133")
(command "_array" "last" "" "R" "75" "3" "25.7867" "24.5283")
(command "_rectangle" "2881,-1934" "2904.5283,-1909.2133")
(command "_array" "last" "" "R" "75" "3" "25.7867" "24.5283")
(command "_rectangle" "2806.415,1" "2829.9433,25.7")
(command "_array" "last" "" "R" "70" "3" "25.7" "24.5283")
(command "_rectangle" "2881,1" "2904.5283,25.7")
(command "_array" "last" "" "R" "70" "3" "25.7" "24.5283")
(command "_rectangle" "2806.415,1801" "2829.9433,1825.9185")
(command "_array" "last" "" "R" "135" "3" "25.9185" "24.5283")
(command "_rectangle" "2881,1801" "2904.5283,1825.9185")
(command "_array" "last" "" "R" "135" "3" "25.9185" "24.5283")
(command "_layer" "set" "vgrooveFDA" "")
(command "_rectangle" "2954.585,-2233" "2805.415,-1933")
(command "_layer" "set" "nitride" "")
(command "_layer" "set" "holes" "")
(command "_circle" "2957.085,331.5" "0.5")
(command "_array" "last" "" "R" "379" "1" "3" "2.5")
(command "_circle" "2802.915,331.5" "0.5")
(command "_array" "last" "" "R" "379" "1" "3" "-2.5")
(command "_layer" "set" "nitride" "")
(command "_layer" "set" "window" "")
(command "_layer" "set" "window" "")
(command "_rectangle" "2959.585,0" "3120.415,1800")
(command "._fillet" "radius" "20" "._fillet" "P" (entlast))
(command "_layer" "set" "grid" "")
(command "_rectangle" "2960.585,1" "2982.4179,25.7")
(command "_array" "last" "" "R" "70" "7" "25.7" "22.8329")
(command "_layer" "set" "nitride" "")
; DRAWING REGION LAYER
(command "_layer" "set" "regionLayer9" "")
(command "_rectangle" "2800,-460" "2960,2260")
(command "_layer" "set" "nitride" "")
(setq coupler9 nil)
(setq singlenanobeam9 nil)
(setq anglednodearray9 nil)
(setq cooledsinglenanobeam9 nil)
(setq yjunction9 nil)
; DEVICE #10
(command "_layer" "set" "window" "")
(command "_circle" "3112.915,-415" "5")
(command "_circle" "3112.915,-402.5" "5")
(command "_circle" "3112.915,-390" "5")
(command "_circle" "3112.915,-377.5" "5")
(command "_circle" "3100.415,-415" "5")
(command "_circle" "3100.415,-402.5" "5")
(command "_circle" "3100.415,-390" "5")
(command "_circle" "3100.415,-377.5" "5")
(command "_circle" "3087.915,-415" "5")
(command "_circle" "3087.915,-402.5" "5")
(command "_layer" "set" "nitride" "")
(setq currobj nil)
(setq currobj (ssadd))
; DRAWING COUPLER
(setq coords (list 
(list 3200.0645 -415) 
(list 3200.0645 -413) 
(list 3273.585 -413) 
(list 3273.585 -413) 
(list 3273.9677 -413.0761) 
(list 3274.2921 -413.2929) 
(list 3274.5089 -413.6173) 
(list 3274.585 -414) 
(list 3274.585 -411.8) 
(list 3274.585 -411.8) 
(list 3274.5089 -412.1827) 
(list 3274.2921 -412.5071) 
(list 3273.9677 -412.7239) 
(list 3273.585 -412.8) 
(list 3200.0645 -412.8) 
(list 3200.0645 -410.8) 
(list 3199.9355 -410.8) 
(list 3199.9355 -412.8) 
(list 3126.415 -412.8) 
(list 3126.0323 -412.7239) 
(list 3125.7079 -412.5071) 
(list 3125.4911 -412.1827) 
(list 3125.415 -411.8) 
(list 3125.415 -411.8) 
(list 3125.415 -414) 
(list 3125.4911 -413.6173) 
(list 3125.7079 -413.2929) 
(list 3126.0323 -413.0761) 
(list 3126.415 -413) 
(list 3126.415 -413) 
(list 3199.9355 -413) 
(list 3199.9355 -415)))
(apply 'command (append '("pline") coords '("c")))
(setq currobj (ssadd (entlast) currobj))
(command "._fillet" "radius" "0.3" "._fillet" "P" (entlast))
(command "_layer" "set" "holes" "")
(command "_circle" "3200,-412.9" "0.113")
(setq currobj (ssadd (entlast) currobj))
(command "_layer" "set" "nitride" "")
(command "_layer" "set" "text" "")
(command "_circle" "3199.2,-415" "0.075")
(command "_circle" "3199.2,-414.7" "0.075")
(command "_circle" "3199.2,-414.4" "0.075")
(command "_circle" "3198.9,-415" "0.075")
(command "_circle" "3198.9,-414.7" "0.075")
(command "_circle" "3198.9,-414.4" "0.075")
(command "_circle" "3198.6,-415" "0.075")
(command "_circle" "3198.6,-414.7" "0.075")
(command "_circle" "3198.6,-414.4" "0.075")
(command "_layer" "set" "nitride" "")
(command "_layer" "set" "prebias" "")
(command "_rectangle" "3125.415,-414" "3274.585,-411.8")
(setq currobj (ssadd (entlast) currobj))
(command "_rectangle" "3199.9355,-415" "3200.0645,-410.8")
(setq currobj (ssadd (entlast) currobj))
(command "_layer" "set" "nitride" "")
(setq coupler10 currobj)
(setq currobj nil)
(setq currobj (ssadd))
; DRAWING SINGLE NANOBEAM
(setq coords (list 
(list 3200.0645 -410.8) 
(list 3200.0645 -409.1417) 
(list 3200.0645 -407.4833) 
(list 3200.0645 -405.825) 
(list 3200.0645 -404.1667) 
(list 3200.0645 -402.5083) 
(list 3200.0645 -400.85) 
(list 3200.0645 -399.1917) 
(list 3200.0645 -397.5333) 
(list 3200.0646 -395.875) 
(list 3200.0646 -394.2167) 
(list 3200.0646 -392.5583) 
(list 3200.0646 -390.9) 
(list 3200.0647 -389.2417) 
(list 3200.0647 -387.5833) 
(list 3200.0647 -385.925) 
(list 3200.0648 -384.2667) 
(list 3200.0648 -382.6083) 
(list 3200.0649 -380.95) 
(list 3200.065 -379.2917) 
(list 3200.0651 -377.6333) 
(list 3200.0651 -375.975) 
(list 3200.0652 -374.3167) 
(list 3200.0653 -372.6583) 
(list 3200.0655 -371) 
(list 3200.0656 -369.3417) 
(list 3200.0657 -367.6833) 
(list 3200.0659 -366.025) 
(list 3200.066 -364.3667) 
(list 3200.0662 -362.7083) 
(list 3200.0664 -361.05) 
(list 3200.0666 -359.3917) 
(list 3200.0668 -357.7333) 
(list 3200.067 -356.075) 
(list 3200.0672 -354.4167) 
(list 3200.0675 -352.7583) 
(list 3200.0678 -351.1) 
(list 3200.068 -349.4417) 
(list 3200.0683 -347.7833) 
(list 3200.0686 -346.125) 
(list 3200.069 -344.4667) 
(list 3200.0693 -342.8083) 
(list 3200.0697 -341.15) 
(list 3200.07 -339.4917) 
(list 3200.0704 -337.8333) 
(list 3200.0709 -336.175) 
(list 3200.0713 -334.5167) 
(list 3200.0717 -332.8583) 
(list 3200.0722 -331.2) 
(list 3200.0727 -329.5417) 
(list 3200.0732 -327.8833) 
(list 3200.0738 -326.225) 
(list 3200.0743 -324.5667) 
(list 3200.0749 -322.9083) 
(list 3200.0755 -321.25) 
(list 3200.0761 -319.5917) 
(list 3200.0767 -317.9333) 
(list 3200.0774 -316.275) 
(list 3200.0781 -314.6167) 
(list 3200.0788 -312.9583) 
(list 3200.0796 -311.3) 
(list 3200.0803 -309.6417) 
(list 3200.0811 -307.9833) 
(list 3200.0819 -306.325) 
(list 3200.0828 -304.6667) 
(list 3200.0837 -303.0083) 
(list 3200.0845 -301.35) 
(list 3200.0855 -299.6917) 
(list 3200.0864 -298.0333) 
(list 3200.0874 -296.375) 
(list 3200.0884 -294.7167) 
(list 3200.0895 -293.0583) 
(list 3200.0905 -291.4) 
(list 3200.0916 -289.7417) 
(list 3200.0928 -288.0833) 
(list 3200.0939 -286.425) 
(list 3200.0951 -284.7667) 
(list 3200.0963 -283.1083) 
(list 3200.0976 -281.45) 
(list 3200.0989 -279.7917) 
(list 3200.1002 -278.1333) 
(list 3200.1016 -276.475) 
(list 3200.1029 -274.8167) 
(list 3200.1044 -273.1583) 
(list 3200.1058 -271.5) 
(list 3200.1073 -269.8417) 
(list 3200.1089 -268.1833) 
(list 3200.1104 -266.525) 
(list 3200.112 -264.8667) 
(list 3200.1137 -263.2083) 
(list 3200.1153 -261.55) 
(list 3200.117 -259.8917) 
(list 3200.1188 -258.2333) 
(list 3200.1206 -256.575) 
(list 3200.1224 -254.9167) 
(list 3200.1243 -253.2583) 
(list 3200.1262 -251.6) 
(list 3200.1281 -249.9417) 
(list 3200.1301 -248.2833) 
(list 3200.1322 -246.625) 
(list 3200.1342 -244.9667) 
(list 3200.1363 -243.3083) 
(list 3200.1385 -241.65) 
(list 3200.1407 -239.9917) 
(list 3200.1429 -238.3333) 
(list 3200.1452 -236.675) 
(list 3200.1476 -235.0167) 
(list 3200.1499 -233.3583) 
(list 3200.1523 -231.7) 
(list 3200.1548 -230.0417) 
(list 3200.1573 -228.3833) 
(list 3200.1599 -226.725) 
(list 3200.1625 -225.0667) 
(list 3200.1651 -223.4083) 
(list 3200.1678 -221.75) 
(list 3200.1706 -220.0917) 
(list 3200.1733 -218.4333) 
(list 3200.1762 -216.775) 
(list 3200.1791 -215.1167) 
(list 3200.182 -213.4583) 
(list 3200.185 -211.8) 
(list 3199.815 -211.8) 
(list 3199.818 -213.4583) 
(list 3199.8209 -215.1167) 
(list 3199.8238 -216.775) 
(list 3199.8267 -218.4333) 
(list 3199.8294 -220.0917) 
(list 3199.8322 -221.75) 
(list 3199.8349 -223.4083) 
(list 3199.8375 -225.0667) 
(list 3199.8401 -226.725) 
(list 3199.8427 -228.3833) 
(list 3199.8452 -230.0417) 
(list 3199.8477 -231.7) 
(list 3199.8501 -233.3583) 
(list 3199.8524 -235.0167) 
(list 3199.8548 -236.675) 
(list 3199.8571 -238.3333) 
(list 3199.8593 -239.9917) 
(list 3199.8615 -241.65) 
(list 3199.8637 -243.3083) 
(list 3199.8658 -244.9667) 
(list 3199.8678 -246.625) 
(list 3199.8699 -248.2833) 
(list 3199.8719 -249.9417) 
(list 3199.8738 -251.6) 
(list 3199.8757 -253.2583) 
(list 3199.8776 -254.9167) 
(list 3199.8794 -256.575) 
(list 3199.8812 -258.2333) 
(list 3199.883 -259.8917) 
(list 3199.8847 -261.55) 
(list 3199.8863 -263.2083) 
(list 3199.888 -264.8667) 
(list 3199.8896 -266.525) 
(list 3199.8911 -268.1833) 
(list 3199.8927 -269.8417) 
(list 3199.8942 -271.5) 
(list 3199.8956 -273.1583) 
(list 3199.8971 -274.8167) 
(list 3199.8984 -276.475) 
(list 3199.8998 -278.1333) 
(list 3199.9011 -279.7917) 
(list 3199.9024 -281.45) 
(list 3199.9037 -283.1083) 
(list 3199.9049 -284.7667) 
(list 3199.9061 -286.425) 
(list 3199.9072 -288.0833) 
(list 3199.9084 -289.7417) 
(list 3199.9095 -291.4) 
(list 3199.9105 -293.0583) 
(list 3199.9116 -294.7167) 
(list 3199.9126 -296.375) 
(list 3199.9136 -298.0333) 
(list 3199.9145 -299.6917) 
(list 3199.9155 -301.35) 
(list 3199.9163 -303.0083) 
(list 3199.9172 -304.6667) 
(list 3199.9181 -306.325) 
(list 3199.9189 -307.9833) 
(list 3199.9197 -309.6417) 
(list 3199.9204 -311.3) 
(list 3199.9212 -312.9583) 
(list 3199.9219 -314.6167) 
(list 3199.9226 -316.275) 
(list 3199.9233 -317.9333) 
(list 3199.9239 -319.5917) 
(list 3199.9245 -321.25) 
(list 3199.9251 -322.9083) 
(list 3199.9257 -324.5667) 
(list 3199.9262 -326.225) 
(list 3199.9268 -327.8833) 
(list 3199.9273 -329.5417) 
(list 3199.9278 -331.2) 
(list 3199.9283 -332.8583) 
(list 3199.9287 -334.5167) 
(list 3199.9291 -336.175) 
(list 3199.9296 -337.8333) 
(list 3199.93 -339.4917) 
(list 3199.9303 -341.15) 
(list 3199.9307 -342.8083) 
(list 3199.931 -344.4667) 
(list 3199.9314 -346.125) 
(list 3199.9317 -347.7833) 
(list 3199.932 -349.4417) 
(list 3199.9322 -351.1) 
(list 3199.9325 -352.7583) 
(list 3199.9328 -354.4167) 
(list 3199.933 -356.075) 
(list 3199.9332 -357.7333) 
(list 3199.9334 -359.3917) 
(list 3199.9336 -361.05) 
(list 3199.9338 -362.7083) 
(list 3199.934 -364.3667) 
(list 3199.9341 -366.025) 
(list 3199.9343 -367.6833) 
(list 3199.9344 -369.3417) 
(list 3199.9345 -371) 
(list 3199.9347 -372.6583) 
(list 3199.9348 -374.3167) 
(list 3199.9349 -375.975) 
(list 3199.9349 -377.6333) 
(list 3199.935 -379.2917) 
(list 3199.9351 -380.95) 
(list 3199.9352 -382.6083) 
(list 3199.9352 -384.2667) 
(list 3199.9353 -385.925) 
(list 3199.9353 -387.5833) 
(list 3199.9353 -389.2417) 
(list 3199.9354 -390.9) 
(list 3199.9354 -392.5583) 
(list 3199.9354 -394.2167) 
(list 3199.9354 -395.875) 
(list 3199.9355 -397.5333) 
(list 3199.9355 -399.1917) 
(list 3199.9355 -400.85) 
(list 3199.9355 -402.5083) 
(list 3199.9355 -404.1667) 
(list 3199.9355 -405.825) 
(list 3199.9355 -407.4833) 
(list 3199.9355 -409.1417) 
(list 3199.9355 -410.8)))
(apply 'command (append '("pline") coords '("c")))
(setq currobj (ssadd (entlast) currobj))
(command "_layer" "set" "prebias" "")
(command "_rectangle" "3199.815,-410.8" "3200.185,-211.8")
(setq currobj (ssadd (entlast) currobj))
(command "_layer" "set" "nitride" "")
(setq singlenanobeam10 currobj)
(setq currobj nil)
(setq currobj (ssadd))
; DRAWING NODE ARRAY
(setq coords (list 
(list 3200.185 -211.8) 
(list 3200.5625 -201.8) 
(list 3200.5625 -201.8) 
(list 3200.5625 -200.8) 
(list 3274.585 -212.6864) 
(list 3274.585 -207.7434) 
(list 3200.5625 -197.357) 
(list 3200.5625 -196.357) 
(list 3200.5625 -196.357) 
(list 3200.2625 -186.357) 
(list 3199.7375 -186.357) 
(list 3199.4375 -196.357) 
(list 3199.4375 -196.357) 
(list 3199.4375 -197.357) 
(list 3125.415 -207.7434) 
(list 3125.415 -212.6864) 
(list 3199.4375 -200.8) 
(list 3199.4375 -201.8) 
(list 3199.4375 -201.8) 
(list 3199.815 -211.8)))
(apply 'command (append '("pline") coords '("c")))
(setq currobj (ssadd (entlast) currobj))
(command "_layer" "set" "prebias" "")
(setq coords (list 
(list 3199.4375 -212.6864) 
(list 3199.4375 -200.8) 
(list 3125.415 -212.6864) 
(list 3125.415 -207.7434) 
(list 3199.4375 -197.357) 
(list 3199.4375 -186.357) 
(list 3200.5625 -186.357) 
(list 3200.5625 -197.357) 
(list 3274.585 -207.7434) 
(list 3274.585 -212.6864) 
(list 3200.5625 -200.8) 
(list 3200.5625 -212.6864)))
(apply 'command (append '("pline") coords '("c")))
(setq currobj (ssadd (entlast) currobj))
(command "_layer" "set" "nitride" "")
(command "_layer" "set" "fda1" "")
(setq coords (list 
(list 3200.5625 -200.657) 
(list 3274.585 -212.5434) 
(list 3274.585 -212.3664) 
(list 3200.5625 -200.58)))
(apply 'command (append '("pline") coords '("c")))
(setq currobj (ssadd (entlast) currobj))
(setq coords (list 
(list 3200.5625 -200.437) 
(list 3274.585 -212.2234) 
(list 3274.585 -212.0464) 
(list 3200.5625 -200.36)))
(apply 'command (append '("pline") coords '("c")))
(setq currobj (ssadd (entlast) currobj))
(setq coords (list 
(list 3200.5625 -200.217) 
(list 3274.585 -211.9034) 
(list 3274.585 -211.7264) 
(list 3200.5625 -200.14)))
(apply 'command (append '("pline") coords '("c")))
(setq currobj (ssadd (entlast) currobj))
(setq coords (list 
(list 3200.5625 -199.997) 
(list 3274.585 -211.5834) 
(list 3274.585 -211.4064) 
(list 3200.5625 -199.92)))
(apply 'command (append '("pline") coords '("c")))
(setq currobj (ssadd (entlast) currobj))
(setq coords (list 
(list 3200.5625 -199.777) 
(list 3274.585 -211.2634) 
(list 3274.585 -211.0864) 
(list 3200.5625 -199.7)))
(apply 'command (append '("pline") coords '("c")))
(setq currobj (ssadd (entlast) currobj))
(setq coords (list 
(list 3200.5625 -199.557) 
(list 3274.585 -210.9434) 
(list 3274.585 -210.7664) 
(list 3200.5625 -199.48)))
(apply 'command (append '("pline") coords '("c")))
(setq currobj (ssadd (entlast) currobj))
(setq coords (list 
(list 3200.5625 -199.337) 
(list 3274.585 -210.6234) 
(list 3274.585 -210.4464) 
(list 3200.5625 -199.26)))
(apply 'command (append '("pline") coords '("c")))
(setq currobj (ssadd (entlast) currobj))
(setq coords (list 
(list 3200.5625 -199.117) 
(list 3274.585 -210.3034) 
(list 3274.585 -210.1264) 
(list 3200.5625 -199.04)))
(apply 'command (append '("pline") coords '("c")))
(setq currobj (ssadd (entlast) currobj))
(setq coords (list 
(list 3200.5625 -198.897) 
(list 3274.585 -209.9834) 
(list 3274.585 -209.8064) 
(list 3200.5625 -198.82)))
(apply 'command (append '("pline") coords '("c")))
(setq currobj (ssadd (entlast) currobj))
(setq coords (list 
(list 3200.5625 -198.677) 
(list 3274.585 -209.6634) 
(list 3274.585 -209.4864) 
(list 3200.5625 -198.6)))
(apply 'command (append '("pline") coords '("c")))
(setq currobj (ssadd (entlast) currobj))
(setq coords (list 
(list 3200.5625 -198.457) 
(list 3274.585 -209.3434) 
(list 3274.585 -209.1664) 
(list 3200.5625 -198.38)))
(apply 'command (append '("pline") coords '("c")))
(setq currobj (ssadd (entlast) currobj))
(setq coords (list 
(list 3200.5625 -198.237) 
(list 3274.585 -209.0234) 
(list 3274.585 -208.8464) 
(list 3200.5625 -198.16)))
(apply 'command (append '("pline") coords '("c")))
(setq currobj (ssadd (entlast) currobj))
(setq coords (list 
(list 3200.5625 -198.017) 
(list 3274.585 -208.7034) 
(list 3274.585 -208.5264) 
(list 3200.5625 -197.94)))
(apply 'command (append '("pline") coords '("c")))
(setq currobj (ssadd (entlast) currobj))
(setq coords (list 
(list 3200.5625 -197.797) 
(list 3274.585 -208.3834) 
(list 3274.585 -208.2064) 
(list 3200.5625 -197.72)))
(apply 'command (append '("pline") coords '("c")))
(setq currobj (ssadd (entlast) currobj))
(setq coords (list 
(list 3200.5625 -197.577) 
(list 3274.585 -208.0634) 
(list 3274.585 -207.8864) 
(list 3200.5625 -197.5)))
(apply 'command (append '("pline") coords '("c")))
(setq currobj (ssadd (entlast) currobj))
(setq coords (list 
(list 3199.4375 -197.5) 
(list 3125.415 -207.8864) 
(list 3125.415 -208.0634) 
(list 3199.4375 -197.577)))
(apply 'command (append '("pline") coords '("c")))
(setq currobj (ssadd (entlast) currobj))
(setq coords (list 
(list 3199.4375 -197.72) 
(list 3125.415 -208.2064) 
(list 3125.415 -208.3834) 
(list 3199.4375 -197.797)))
(apply 'command (append '("pline") coords '("c")))
(setq currobj (ssadd (entlast) currobj))
(setq coords (list 
(list 3199.4375 -197.94) 
(list 3125.415 -208.5264) 
(list 3125.415 -208.7034) 
(list 3199.4375 -198.017)))
(apply 'command (append '("pline") coords '("c")))
(setq currobj (ssadd (entlast) currobj))
(setq coords (list 
(list 3199.4375 -198.16) 
(list 3125.415 -208.8464) 
(list 3125.415 -209.0234) 
(list 3199.4375 -198.237)))
(apply 'command (append '("pline") coords '("c")))
(setq currobj (ssadd (entlast) currobj))
(setq coords (list 
(list 3199.4375 -198.38) 
(list 3125.415 -209.1664) 
(list 3125.415 -209.3434) 
(list 3199.4375 -198.457)))
(apply 'command (append '("pline") coords '("c")))
(setq currobj (ssadd (entlast) currobj))
(setq coords (list 
(list 3199.4375 -198.6) 
(list 3125.415 -209.4864) 
(list 3125.415 -209.6634) 
(list 3199.4375 -198.677)))
(apply 'command (append '("pline") coords '("c")))
(setq currobj (ssadd (entlast) currobj))
(setq coords (list 
(list 3199.4375 -198.82) 
(list 3125.415 -209.8064) 
(list 3125.415 -209.9834) 
(list 3199.4375 -198.897)))
(apply 'command (append '("pline") coords '("c")))
(setq currobj (ssadd (entlast) currobj))
(setq coords (list 
(list 3199.4375 -199.04) 
(list 3125.415 -210.1264) 
(list 3125.415 -210.3034) 
(list 3199.4375 -199.117)))
(apply 'command (append '("pline") coords '("c")))
(setq currobj (ssadd (entlast) currobj))
(setq coords (list 
(list 3199.4375 -199.26) 
(list 3125.415 -210.4464) 
(list 3125.415 -210.6234) 
(list 3199.4375 -199.337)))
(apply 'command (append '("pline") coords '("c")))
(setq currobj (ssadd (entlast) currobj))
(setq coords (list 
(list 3199.4375 -199.48) 
(list 3125.415 -210.7664) 
(list 3125.415 -210.9434) 
(list 3199.4375 -199.557)))
(apply 'command (append '("pline") coords '("c")))
(setq currobj (ssadd (entlast) currobj))
(setq coords (list 
(list 3199.4375 -199.7) 
(list 3125.415 -211.0864) 
(list 3125.415 -211.2634) 
(list 3199.4375 -199.777)))
(apply 'command (append '("pline") coords '("c")))
(setq currobj (ssadd (entlast) currobj))
(setq coords (list 
(list 3199.4375 -199.92) 
(list 3125.415 -211.4064) 
(list 3125.415 -211.5834) 
(list 3199.4375 -199.997)))
(apply 'command (append '("pline") coords '("c")))
(setq currobj (ssadd (entlast) currobj))
(setq coords (list 
(list 3199.4375 -200.14) 
(list 3125.415 -211.7264) 
(list 3125.415 -211.9034) 
(list 3199.4375 -200.217)))
(apply 'command (append '("pline") coords '("c")))
(setq currobj (ssadd (entlast) currobj))
(setq coords (list 
(list 3199.4375 -200.36) 
(list 3125.415 -212.0464) 
(list 3125.415 -212.2234) 
(list 3199.4375 -200.437)))
(apply 'command (append '("pline") coords '("c")))
(setq currobj (ssadd (entlast) currobj))
(setq coords (list 
(list 3199.4375 -200.58) 
(list 3125.415 -212.3664) 
(list 3125.415 -212.5434) 
(list 3199.4375 -200.657)))
(apply 'command (append '("pline") coords '("c")))
(setq currobj (ssadd (entlast) currobj))
(command "_layer" "set" "nitride" "")
(command "_layer" "set" "text" "")
(command "_circle" "3198.985,-211.8" "0.075")
(command "_circle" "3198.985,-211.5" "0.075")
(command "_circle" "3198.985,-211.2" "0.075")
(command "_circle" "3198.985,-210.9" "0.075")
(command "_circle" "3198.985,-210.6" "0.075")
(command "_circle" "3198.685,-211.8" "0.075")
(command "_circle" "3198.685,-211.5" "0.075")
(command "_circle" "3198.685,-211.2" "0.075")
(command "_circle" "3198.685,-210.9" "0.075")
(command "_circle" "3198.685,-210.6" "0.075")
(command "_circle" "3198.385,-211.8" "0.075")
(command "_circle" "3198.385,-211.5" "0.075")
(command "_circle" "3198.385,-211.2" "0.075")
(command "_circle" "3198.385,-210.9" "0.075")
(command "_circle" "3198.385,-210.6" "0.075")
(command "_circle" "3198.085,-211.8" "0.075")
(command "_circle" "3198.085,-211.5" "0.075")
(command "_circle" "3198.085,-211.2" "0.075")
(command "_circle" "3198.085,-210.9" "0.075")
(command "_circle" "3198.085,-210.6" "0.075")
(command "_circle" "3197.785,-211.8" "0.075")
(command "_circle" "3197.785,-211.5" "0.075")
(command "_circle" "3197.785,-211.2" "0.075")
(command "_circle" "3197.785,-210.9" "0.075")
(command "_circle" "3197.785,-210.6" "0.075")
(command "_layer" "set" "nitride" "")
(setq anglednodearray10 currobj)
(setq currobj nil)
(setq currobj (ssadd))
; DRAWING COOLED SINGLE NANOBEAM
(setq coords (list 
(list 3200.2625 -186.357) 
(list 3200.2625 -181.357) 
(list 3199.7375 -181.357) 
(list 3199.7375 -186.357)))
(apply 'command (append '("pline") coords '("c")))
(setq currobj (ssadd (entlast) currobj))
(command "_layer" "set" "prebias" "")
(command "_rectangle" "3199.7375,-186.357" "3200.2625,-181.357")
(setq currobj (ssadd (entlast) currobj))
(command "_layer" "set" "nitride" "")
(setq coords (list 
(list 3200.2625 -181.357) 
(list 3200.5625 -171.357) 
(list 3200.5625 -171.357) 
(list 3200.5625 -170.357) 
(list 3274.585 -171.107) 
(list 3274.585 -166.164) 
(list 3200.5625 -166.914) 
(list 3200.5625 -165.914) 
(list 3200.5625 -165.914) 
(list 3200.2625 -155.914) 
(list 3199.7375 -155.914) 
(list 3199.4375 -165.914) 
(list 3199.4375 -165.914) 
(list 3199.4375 -166.914) 
(list 3125.415 -166.164) 
(list 3125.415 -171.107) 
(list 3199.4375 -170.357) 
(list 3199.4375 -171.357) 
(list 3199.4375 -171.357) 
(list 3199.7375 -181.357)))
(apply 'command (append '("pline") coords '("c")))
(setq currobj (ssadd (entlast) currobj))
(command "_layer" "set" "prebias" "")
(setq coords (list 
(list 3199.4375 -181.357) 
(list 3199.4375 -170.357) 
(list 3125.415 -171.107) 
(list 3125.415 -166.164) 
(list 3199.4375 -166.914) 
(list 3199.4375 -155.914) 
(list 3200.5625 -155.914) 
(list 3200.5625 -166.914) 
(list 3274.585 -166.164) 
(list 3274.585 -171.107) 
(list 3200.5625 -170.357) 
(list 3200.5625 -181.357)))
(apply 'command (append '("pline") coords '("c")))
(setq currobj (ssadd (entlast) currobj))
(command "_layer" "set" "nitride" "")
(command "_layer" "set" "fda1" "")
(setq coords (list 
(list 3200.5625 -170.214) 
(list 3274.585 -170.964) 
(list 3274.585 -170.787) 
(list 3200.5625 -170.137)))
(apply 'command (append '("pline") coords '("c")))
(setq currobj (ssadd (entlast) currobj))
(setq coords (list 
(list 3200.5625 -169.994) 
(list 3274.585 -170.644) 
(list 3274.585 -170.467) 
(list 3200.5625 -169.917)))
(apply 'command (append '("pline") coords '("c")))
(setq currobj (ssadd (entlast) currobj))
(setq coords (list 
(list 3200.5625 -169.774) 
(list 3274.585 -170.324) 
(list 3274.585 -170.147) 
(list 3200.5625 -169.697)))
(apply 'command (append '("pline") coords '("c")))
(setq currobj (ssadd (entlast) currobj))
(setq coords (list 
(list 3200.5625 -169.554) 
(list 3274.585 -170.004) 
(list 3274.585 -169.827) 
(list 3200.5625 -169.477)))
(apply 'command (append '("pline") coords '("c")))
(setq currobj (ssadd (entlast) currobj))
(setq coords (list 
(list 3200.5625 -169.334) 
(list 3274.585 -169.684) 
(list 3274.585 -169.507) 
(list 3200.5625 -169.257)))
(apply 'command (append '("pline") coords '("c")))
(setq currobj (ssadd (entlast) currobj))
(setq coords (list 
(list 3200.5625 -169.114) 
(list 3274.585 -169.364) 
(list 3274.585 -169.187) 
(list 3200.5625 -169.037)))
(apply 'command (append '("pline") coords '("c")))
(setq currobj (ssadd (entlast) currobj))
(setq coords (list 
(list 3200.5625 -168.894) 
(list 3274.585 -169.044) 
(list 3274.585 -168.867) 
(list 3200.5625 -168.817)))
(apply 'command (append '("pline") coords '("c")))
(setq currobj (ssadd (entlast) currobj))
(setq coords (list 
(list 3200.5625 -168.674) 
(list 3274.585 -168.724) 
(list 3274.585 -168.547) 
(list 3200.5625 -168.597)))
(apply 'command (append '("pline") coords '("c")))
(setq currobj (ssadd (entlast) currobj))
(setq coords (list 
(list 3200.5625 -168.454) 
(list 3274.585 -168.404) 
(list 3274.585 -168.227) 
(list 3200.5625 -168.377)))
(apply 'command (append '("pline") coords '("c")))
(setq currobj (ssadd (entlast) currobj))
(setq coords (list 
(list 3200.5625 -168.234) 
(list 3274.585 -168.084) 
(list 3274.585 -167.907) 
(list 3200.5625 -168.157)))
(apply 'command (append '("pline") coords '("c")))
(setq currobj (ssadd (entlast) currobj))
(setq coords (list 
(list 3200.5625 -168.014) 
(list 3274.585 -167.764) 
(list 3274.585 -167.587) 
(list 3200.5625 -167.937)))
(apply 'command (append '("pline") coords '("c")))
(setq currobj (ssadd (entlast) currobj))
(setq coords (list 
(list 3200.5625 -167.794) 
(list 3274.585 -167.444) 
(list 3274.585 -167.267) 
(list 3200.5625 -167.717)))
(apply 'command (append '("pline") coords '("c")))
(setq currobj (ssadd (entlast) currobj))
(setq coords (list 
(list 3200.5625 -167.574) 
(list 3274.585 -167.124) 
(list 3274.585 -166.947) 
(list 3200.5625 -167.497)))
(apply 'command (append '("pline") coords '("c")))
(setq currobj (ssadd (entlast) currobj))
(setq coords (list 
(list 3200.5625 -167.354) 
(list 3274.585 -166.804) 
(list 3274.585 -166.627) 
(list 3200.5625 -167.277)))
(apply 'command (append '("pline") coords '("c")))
(setq currobj (ssadd (entlast) currobj))
(setq coords (list 
(list 3200.5625 -167.134) 
(list 3274.585 -166.484) 
(list 3274.585 -166.307) 
(list 3200.5625 -167.057)))
(apply 'command (append '("pline") coords '("c")))
(setq currobj (ssadd (entlast) currobj))
(setq coords (list 
(list 3199.4375 -167.057) 
(list 3125.415 -166.307) 
(list 3125.415 -166.484) 
(list 3199.4375 -167.134)))
(apply 'command (append '("pline") coords '("c")))
(setq currobj (ssadd (entlast) currobj))
(setq coords (list 
(list 3199.4375 -167.277) 
(list 3125.415 -166.627) 
(list 3125.415 -166.804) 
(list 3199.4375 -167.354)))
(apply 'command (append '("pline") coords '("c")))
(setq currobj (ssadd (entlast) currobj))
(setq coords (list 
(list 3199.4375 -167.497) 
(list 3125.415 -166.947) 
(list 3125.415 -167.124) 
(list 3199.4375 -167.574)))
(apply 'command (append '("pline") coords '("c")))
(setq currobj (ssadd (entlast) currobj))
(setq coords (list 
(list 3199.4375 -167.717) 
(list 3125.415 -167.267) 
(list 3125.415 -167.444) 
(list 3199.4375 -167.794)))
(apply 'command (append '("pline") coords '("c")))
(setq currobj (ssadd (entlast) currobj))
(setq coords (list 
(list 3199.4375 -167.937) 
(list 3125.415 -167.587) 
(list 3125.415 -167.764) 
(list 3199.4375 -168.014)))
(apply 'command (append '("pline") coords '("c")))
(setq currobj (ssadd (entlast) currobj))
(setq coords (list 
(list 3199.4375 -168.157) 
(list 3125.415 -167.907) 
(list 3125.415 -168.084) 
(list 3199.4375 -168.234)))
(apply 'command (append '("pline") coords '("c")))
(setq currobj (ssadd (entlast) currobj))
(setq coords (list 
(list 3199.4375 -168.377) 
(list 3125.415 -168.227) 
(list 3125.415 -168.404) 
(list 3199.4375 -168.454)))
(apply 'command (append '("pline") coords '("c")))
(setq currobj (ssadd (entlast) currobj))
(setq coords (list 
(list 3199.4375 -168.597) 
(list 3125.415 -168.547) 
(list 3125.415 -168.724) 
(list 3199.4375 -168.674)))
(apply 'command (append '("pline") coords '("c")))
(setq currobj (ssadd (entlast) currobj))
(setq coords (list 
(list 3199.4375 -168.817) 
(list 3125.415 -168.867) 
(list 3125.415 -169.044) 
(list 3199.4375 -168.894)))
(apply 'command (append '("pline") coords '("c")))
(setq currobj (ssadd (entlast) currobj))
(setq coords (list 
(list 3199.4375 -169.037) 
(list 3125.415 -169.187) 
(list 3125.415 -169.364) 
(list 3199.4375 -169.114)))
(apply 'command (append '("pline") coords '("c")))
(setq currobj (ssadd (entlast) currobj))
(setq coords (list 
(list 3199.4375 -169.257) 
(list 3125.415 -169.507) 
(list 3125.415 -169.684) 
(list 3199.4375 -169.334)))
(apply 'command (append '("pline") coords '("c")))
(setq currobj (ssadd (entlast) currobj))
(setq coords (list 
(list 3199.4375 -169.477) 
(list 3125.415 -169.827) 
(list 3125.415 -170.004) 
(list 3199.4375 -169.554)))
(apply 'command (append '("pline") coords '("c")))
(setq currobj (ssadd (entlast) currobj))
(setq coords (list 
(list 3199.4375 -169.697) 
(list 3125.415 -170.147) 
(list 3125.415 -170.324) 
(list 3199.4375 -169.774)))
(apply 'command (append '("pline") coords '("c")))
(setq currobj (ssadd (entlast) currobj))
(setq coords (list 
(list 3199.4375 -169.917) 
(list 3125.415 -170.467) 
(list 3125.415 -170.644) 
(list 3199.4375 -169.994)))
(apply 'command (append '("pline") coords '("c")))
(setq currobj (ssadd (entlast) currobj))
(setq coords (list 
(list 3199.4375 -170.137) 
(list 3125.415 -170.787) 
(list 3125.415 -170.964) 
(list 3199.4375 -170.214)))
(apply 'command (append '("pline") coords '("c")))
(setq currobj (ssadd (entlast) currobj))
(command "_layer" "set" "nitride" "")
(command "_layer" "set" "text" "")
(command "_circle" "3199.0625,-181.357" "0.075")
(command "_circle" "3199.0625,-181.057" "0.075")
(command "_circle" "3199.0625,-180.757" "0.075")
(command "_circle" "3199.0625,-180.457" "0.075")
(command "_circle" "3199.0625,-180.157" "0.075")
(command "_circle" "3198.7625,-181.357" "0.075")
(command "_circle" "3198.7625,-181.057" "0.075")
(command "_circle" "3198.7625,-180.757" "0.075")
(command "_circle" "3198.7625,-180.457" "0.075")
(command "_circle" "3198.7625,-180.157" "0.075")
(command "_circle" "3198.4625,-181.357" "0.075")
(command "_circle" "3198.4625,-181.057" "0.075")
(command "_circle" "3198.4625,-180.757" "0.075")
(command "_circle" "3198.4625,-180.457" "0.075")
(command "_circle" "3198.4625,-180.157" "0.075")
(command "_circle" "3198.1625,-181.357" "0.075")
(command "_circle" "3198.1625,-181.057" "0.075")
(command "_circle" "3198.1625,-180.757" "0.075")
(command "_circle" "3198.1625,-180.457" "0.075")
(command "_circle" "3198.1625,-180.157" "0.075")
(command "_circle" "3197.8625,-181.357" "0.075")
(command "_circle" "3197.8625,-181.057" "0.075")
(command "_circle" "3197.8625,-180.757" "0.075")
(command "_circle" "3197.8625,-180.457" "0.075")
(command "_circle" "3197.8625,-180.157" "0.075")
(command "_layer" "set" "nitride" "")
(setq coords (list 
(list 3200.2625 -155.914) 
(list 3200.2625 -40.2693) 
(list 3199.7375 -40.2693) 
(list 3199.7375 -155.914)))
(apply 'command (append '("pline") coords '("c")))
(setq currobj (ssadd (entlast) currobj))
(command "_layer" "set" "prebias" "")
(command "_rectangle" "3199.7375,-155.914" "3200.2625,-40.2693")
(setq currobj (ssadd (entlast) currobj))
(command "_layer" "set" "nitride" "")
(setq coords (list 
(list 3200.2625 -40.2693) 
(list 3200.5625 -30.2693) 
(list 3200.5625 -30.2693) 
(list 3200.5625 -29.2693) 
(list 3274.585 -30.0193) 
(list 3274.585 -25.0763) 
(list 3200.5625 -25.8263) 
(list 3200.5625 -24.8263) 
(list 3200.5625 -24.8263) 
(list 3200.2625 -14.8263) 
(list 3199.7375 -14.8263) 
(list 3199.4375 -24.8263) 
(list 3199.4375 -24.8263) 
(list 3199.4375 -25.8263) 
(list 3125.415 -25.0763) 
(list 3125.415 -30.0193) 
(list 3199.4375 -29.2693) 
(list 3199.4375 -30.2693) 
(list 3199.4375 -30.2693) 
(list 3199.7375 -40.2693)))
(apply 'command (append '("pline") coords '("c")))
(setq currobj (ssadd (entlast) currobj))
(command "_layer" "set" "prebias" "")
(setq coords (list 
(list 3199.4375 -40.2693) 
(list 3199.4375 -29.2693) 
(list 3125.415 -30.0193) 
(list 3125.415 -25.0763) 
(list 3199.4375 -25.8263) 
(list 3199.4375 -14.8263) 
(list 3200.5625 -14.8263) 
(list 3200.5625 -25.8263) 
(list 3274.585 -25.0763) 
(list 3274.585 -30.0193) 
(list 3200.5625 -29.2693) 
(list 3200.5625 -40.2693)))
(apply 'command (append '("pline") coords '("c")))
(setq currobj (ssadd (entlast) currobj))
(command "_layer" "set" "nitride" "")
(command "_layer" "set" "fda1" "")
(setq coords (list 
(list 3200.5625 -29.1263) 
(list 3274.585 -29.8763) 
(list 3274.585 -29.6993) 
(list 3200.5625 -29.0493)))
(apply 'command (append '("pline") coords '("c")))
(setq currobj (ssadd (entlast) currobj))
(setq coords (list 
(list 3200.5625 -28.9063) 
(list 3274.585 -29.5563) 
(list 3274.585 -29.3793) 
(list 3200.5625 -28.8293)))
(apply 'command (append '("pline") coords '("c")))
(setq currobj (ssadd (entlast) currobj))
(setq coords (list 
(list 3200.5625 -28.6863) 
(list 3274.585 -29.2363) 
(list 3274.585 -29.0593) 
(list 3200.5625 -28.6093)))
(apply 'command (append '("pline") coords '("c")))
(setq currobj (ssadd (entlast) currobj))
(setq coords (list 
(list 3200.5625 -28.4663) 
(list 3274.585 -28.9163) 
(list 3274.585 -28.7393) 
(list 3200.5625 -28.3893)))
(apply 'command (append '("pline") coords '("c")))
(setq currobj (ssadd (entlast) currobj))
(setq coords (list 
(list 3200.5625 -28.2463) 
(list 3274.585 -28.5963) 
(list 3274.585 -28.4193) 
(list 3200.5625 -28.1693)))
(apply 'command (append '("pline") coords '("c")))
(setq currobj (ssadd (entlast) currobj))
(setq coords (list 
(list 3200.5625 -28.0263) 
(list 3274.585 -28.2763) 
(list 3274.585 -28.0993) 
(list 3200.5625 -27.9493)))
(apply 'command (append '("pline") coords '("c")))
(setq currobj (ssadd (entlast) currobj))
(setq coords (list 
(list 3200.5625 -27.8063) 
(list 3274.585 -27.9563) 
(list 3274.585 -27.7793) 
(list 3200.5625 -27.7293)))
(apply 'command (append '("pline") coords '("c")))
(setq currobj (ssadd (entlast) currobj))
(setq coords (list 
(list 3200.5625 -27.5863) 
(list 3274.585 -27.6363) 
(list 3274.585 -27.4593) 
(list 3200.5625 -27.5093)))
(apply 'command (append '("pline") coords '("c")))
(setq currobj (ssadd (entlast) currobj))
(setq coords (list 
(list 3200.5625 -27.3663) 
(list 3274.585 -27.3163) 
(list 3274.585 -27.1393) 
(list 3200.5625 -27.2893)))
(apply 'command (append '("pline") coords '("c")))
(setq currobj (ssadd (entlast) currobj))
(setq coords (list 
(list 3200.5625 -27.1463) 
(list 3274.585 -26.9963) 
(list 3274.585 -26.8193) 
(list 3200.5625 -27.0693)))
(apply 'command (append '("pline") coords '("c")))
(setq currobj (ssadd (entlast) currobj))
(setq coords (list 
(list 3200.5625 -26.9263) 
(list 3274.585 -26.6763) 
(list 3274.585 -26.4993) 
(list 3200.5625 -26.8493)))
(apply 'command (append '("pline") coords '("c")))
(setq currobj (ssadd (entlast) currobj))
(setq coords (list 
(list 3200.5625 -26.7063) 
(list 3274.585 -26.3563) 
(list 3274.585 -26.1793) 
(list 3200.5625 -26.6293)))
(apply 'command (append '("pline") coords '("c")))
(setq currobj (ssadd (entlast) currobj))
(setq coords (list 
(list 3200.5625 -26.4863) 
(list 3274.585 -26.0363) 
(list 3274.585 -25.8593) 
(list 3200.5625 -26.4093)))
(apply 'command (append '("pline") coords '("c")))
(setq currobj (ssadd (entlast) currobj))
(setq coords (list 
(list 3200.5625 -26.2663) 
(list 3274.585 -25.7163) 
(list 3274.585 -25.5393) 
(list 3200.5625 -26.1893)))
(apply 'command (append '("pline") coords '("c")))
(setq currobj (ssadd (entlast) currobj))
(setq coords (list 
(list 3200.5625 -26.0463) 
(list 3274.585 -25.3963) 
(list 3274.585 -25.2193) 
(list 3200.5625 -25.9693)))
(apply 'command (append '("pline") coords '("c")))
(setq currobj (ssadd (entlast) currobj))
(setq coords (list 
(list 3199.4375 -25.9693) 
(list 3125.415 -25.2193) 
(list 3125.415 -25.3963) 
(list 3199.4375 -26.0463)))
(apply 'command (append '("pline") coords '("c")))
(setq currobj (ssadd (entlast) currobj))
(setq coords (list 
(list 3199.4375 -26.1893) 
(list 3125.415 -25.5393) 
(list 3125.415 -25.7163) 
(list 3199.4375 -26.2663)))
(apply 'command (append '("pline") coords '("c")))
(setq currobj (ssadd (entlast) currobj))
(setq coords (list 
(list 3199.4375 -26.4093) 
(list 3125.415 -25.8593) 
(list 3125.415 -26.0363) 
(list 3199.4375 -26.4863)))
(apply 'command (append '("pline") coords '("c")))
(setq currobj (ssadd (entlast) currobj))
(setq coords (list 
(list 3199.4375 -26.6293) 
(list 3125.415 -26.1793) 
(list 3125.415 -26.3563) 
(list 3199.4375 -26.7063)))
(apply 'command (append '("pline") coords '("c")))
(setq currobj (ssadd (entlast) currobj))
(setq coords (list 
(list 3199.4375 -26.8493) 
(list 3125.415 -26.4993) 
(list 3125.415 -26.6763) 
(list 3199.4375 -26.9263)))
(apply 'command (append '("pline") coords '("c")))
(setq currobj (ssadd (entlast) currobj))
(setq coords (list 
(list 3199.4375 -27.0693) 
(list 3125.415 -26.8193) 
(list 3125.415 -26.9963) 
(list 3199.4375 -27.1463)))
(apply 'command (append '("pline") coords '("c")))
(setq currobj (ssadd (entlast) currobj))
(setq coords (list 
(list 3199.4375 -27.2893) 
(list 3125.415 -27.1393) 
(list 3125.415 -27.3163) 
(list 3199.4375 -27.3663)))
(apply 'command (append '("pline") coords '("c")))
(setq currobj (ssadd (entlast) currobj))
(setq coords (list 
(list 3199.4375 -27.5093) 
(list 3125.415 -27.4593) 
(list 3125.415 -27.6363) 
(list 3199.4375 -27.5863)))
(apply 'command (append '("pline") coords '("c")))
(setq currobj (ssadd (entlast) currobj))
(setq coords (list 
(list 3199.4375 -27.7293) 
(list 3125.415 -27.7793) 
(list 3125.415 -27.9563) 
(list 3199.4375 -27.8063)))
(apply 'command (append '("pline") coords '("c")))
(setq currobj (ssadd (entlast) currobj))
(setq coords (list 
(list 3199.4375 -27.9493) 
(list 3125.415 -28.0993) 
(list 3125.415 -28.2763) 
(list 3199.4375 -28.0263)))
(apply 'command (append '("pline") coords '("c")))
(setq currobj (ssadd (entlast) currobj))
(setq coords (list 
(list 3199.4375 -28.1693) 
(list 3125.415 -28.4193) 
(list 3125.415 -28.5963) 
(list 3199.4375 -28.2463)))
(apply 'command (append '("pline") coords '("c")))
(setq currobj (ssadd (entlast) currobj))
(setq coords (list 
(list 3199.4375 -28.3893) 
(list 3125.415 -28.7393) 
(list 3125.415 -28.9163) 
(list 3199.4375 -28.4663)))
(apply 'command (append '("pline") coords '("c")))
(setq currobj (ssadd (entlast) currobj))
(setq coords (list 
(list 3199.4375 -28.6093) 
(list 3125.415 -29.0593) 
(list 3125.415 -29.2363) 
(list 3199.4375 -28.6863)))
(apply 'command (append '("pline") coords '("c")))
(setq currobj (ssadd (entlast) currobj))
(setq coords (list 
(list 3199.4375 -28.8293) 
(list 3125.415 -29.3793) 
(list 3125.415 -29.5563) 
(list 3199.4375 -28.9063)))
(apply 'command (append '("pline") coords '("c")))
(setq currobj (ssadd (entlast) currobj))
(setq coords (list 
(list 3199.4375 -29.0493) 
(list 3125.415 -29.6993) 
(list 3125.415 -29.8763) 
(list 3199.4375 -29.1263)))
(apply 'command (append '("pline") coords '("c")))
(setq currobj (ssadd (entlast) currobj))
(command "_layer" "set" "nitride" "")
(command "_layer" "set" "text" "")
(command "_circle" "3199.0625,-40.2693" "0.075")
(command "_circle" "3199.0625,-39.9693" "0.075")
(command "_circle" "3199.0625,-39.6693" "0.075")
(command "_circle" "3199.0625,-39.3693" "0.075")
(command "_circle" "3199.0625,-39.0693" "0.075")
(command "_circle" "3198.7625,-40.2693" "0.075")
(command "_circle" "3198.7625,-39.9693" "0.075")
(command "_circle" "3198.7625,-39.6693" "0.075")
(command "_circle" "3198.7625,-39.3693" "0.075")
(command "_circle" "3198.7625,-39.0693" "0.075")
(command "_circle" "3198.4625,-40.2693" "0.075")
(command "_circle" "3198.4625,-39.9693" "0.075")
(command "_circle" "3198.4625,-39.6693" "0.075")
(command "_circle" "3198.4625,-39.3693" "0.075")
(command "_circle" "3198.4625,-39.0693" "0.075")
(command "_circle" "3198.1625,-40.2693" "0.075")
(command "_circle" "3198.1625,-39.9693" "0.075")
(command "_circle" "3198.1625,-39.6693" "0.075")
(command "_circle" "3198.1625,-39.3693" "0.075")
(command "_circle" "3198.1625,-39.0693" "0.075")
(command "_circle" "3197.8625,-40.2693" "0.075")
(command "_circle" "3197.8625,-39.9693" "0.075")
(command "_circle" "3197.8625,-39.6693" "0.075")
(command "_circle" "3197.8625,-39.3693" "0.075")
(command "_circle" "3197.8625,-39.0693" "0.075")
(command "_layer" "set" "nitride" "")
(setq coords (list 
(list 3200.2625 -14.8263) 
(list 3200.2625 100.8184) 
(list 3199.7375 100.8184) 
(list 3199.7375 -14.8263)))
(apply 'command (append '("pline") coords '("c")))
(setq currobj (ssadd (entlast) currobj))
(command "_layer" "set" "prebias" "")
(command "_rectangle" "3199.7375,-14.8263" "3200.2625,100.8184")
(setq currobj (ssadd (entlast) currobj))
(command "_layer" "set" "nitride" "")
(setq coords (list 
(list 3200.2625 100.8184) 
(list 3200.5625 110.8184) 
(list 3200.5625 110.8184) 
(list 3200.5625 111.8184) 
(list 3274.585 111.0684) 
(list 3274.585 116.0114) 
(list 3200.5625 115.2614) 
(list 3200.5625 116.2614) 
(list 3200.5625 116.2614) 
(list 3200.2625 126.2614) 
(list 3199.7375 126.2614) 
(list 3199.4375 116.2614) 
(list 3199.4375 116.2614) 
(list 3199.4375 115.2614) 
(list 3125.415 116.0114) 
(list 3125.415 111.0684) 
(list 3199.4375 111.8184) 
(list 3199.4375 110.8184) 
(list 3199.4375 110.8184) 
(list 3199.7375 100.8184)))
(apply 'command (append '("pline") coords '("c")))
(setq currobj (ssadd (entlast) currobj))
(command "_layer" "set" "prebias" "")
(setq coords (list 
(list 3199.4375 100.8184) 
(list 3199.4375 111.8184) 
(list 3125.415 111.0684) 
(list 3125.415 116.0114) 
(list 3199.4375 115.2614) 
(list 3199.4375 126.2614) 
(list 3200.5625 126.2614) 
(list 3200.5625 115.2614) 
(list 3274.585 116.0114) 
(list 3274.585 111.0684) 
(list 3200.5625 111.8184) 
(list 3200.5625 100.8184)))
(apply 'command (append '("pline") coords '("c")))
(setq currobj (ssadd (entlast) currobj))
(command "_layer" "set" "nitride" "")
(command "_layer" "set" "fda1" "")
(setq coords (list 
(list 3200.5625 111.9614) 
(list 3274.585 111.2114) 
(list 3274.585 111.3884) 
(list 3200.5625 112.0384)))
(apply 'command (append '("pline") coords '("c")))
(setq currobj (ssadd (entlast) currobj))
(setq coords (list 
(list 3200.5625 112.1814) 
(list 3274.585 111.5314) 
(list 3274.585 111.7084) 
(list 3200.5625 112.2584)))
(apply 'command (append '("pline") coords '("c")))
(setq currobj (ssadd (entlast) currobj))
(setq coords (list 
(list 3200.5625 112.4014) 
(list 3274.585 111.8514) 
(list 3274.585 112.0284) 
(list 3200.5625 112.4784)))
(apply 'command (append '("pline") coords '("c")))
(setq currobj (ssadd (entlast) currobj))
(setq coords (list 
(list 3200.5625 112.6214) 
(list 3274.585 112.1714) 
(list 3274.585 112.3484) 
(list 3200.5625 112.6984)))
(apply 'command (append '("pline") coords '("c")))
(setq currobj (ssadd (entlast) currobj))
(setq coords (list 
(list 3200.5625 112.8414) 
(list 3274.585 112.4914) 
(list 3274.585 112.6684) 
(list 3200.5625 112.9184)))
(apply 'command (append '("pline") coords '("c")))
(setq currobj (ssadd (entlast) currobj))
(setq coords (list 
(list 3200.5625 113.0614) 
(list 3274.585 112.8114) 
(list 3274.585 112.9884) 
(list 3200.5625 113.1384)))
(apply 'command (append '("pline") coords '("c")))
(setq currobj (ssadd (entlast) currobj))
(setq coords (list 
(list 3200.5625 113.2814) 
(list 3274.585 113.1314) 
(list 3274.585 113.3084) 
(list 3200.5625 113.3584)))
(apply 'command (append '("pline") coords '("c")))
(setq currobj (ssadd (entlast) currobj))
(setq coords (list 
(list 3200.5625 113.5014) 
(list 3274.585 113.4514) 
(list 3274.585 113.6284) 
(list 3200.5625 113.5784)))
(apply 'command (append '("pline") coords '("c")))
(setq currobj (ssadd (entlast) currobj))
(setq coords (list 
(list 3200.5625 113.7214) 
(list 3274.585 113.7714) 
(list 3274.585 113.9484) 
(list 3200.5625 113.7984)))
(apply 'command (append '("pline") coords '("c")))
(setq currobj (ssadd (entlast) currobj))
(setq coords (list 
(list 3200.5625 113.9414) 
(list 3274.585 114.0914) 
(list 3274.585 114.2684) 
(list 3200.5625 114.0184)))
(apply 'command (append '("pline") coords '("c")))
(setq currobj (ssadd (entlast) currobj))
(setq coords (list 
(list 3200.5625 114.1614) 
(list 3274.585 114.4114) 
(list 3274.585 114.5884) 
(list 3200.5625 114.2384)))
(apply 'command (append '("pline") coords '("c")))
(setq currobj (ssadd (entlast) currobj))
(setq coords (list 
(list 3200.5625 114.3814) 
(list 3274.585 114.7314) 
(list 3274.585 114.9084) 
(list 3200.5625 114.4584)))
(apply 'command (append '("pline") coords '("c")))
(setq currobj (ssadd (entlast) currobj))
(setq coords (list 
(list 3200.5625 114.6014) 
(list 3274.585 115.0514) 
(list 3274.585 115.2284) 
(list 3200.5625 114.6784)))
(apply 'command (append '("pline") coords '("c")))
(setq currobj (ssadd (entlast) currobj))
(setq coords (list 
(list 3200.5625 114.8214) 
(list 3274.585 115.3714) 
(list 3274.585 115.5484) 
(list 3200.5625 114.8984)))
(apply 'command (append '("pline") coords '("c")))
(setq currobj (ssadd (entlast) currobj))
(setq coords (list 
(list 3200.5625 115.0414) 
(list 3274.585 115.6914) 
(list 3274.585 115.8684) 
(list 3200.5625 115.1184)))
(apply 'command (append '("pline") coords '("c")))
(setq currobj (ssadd (entlast) currobj))
(setq coords (list 
(list 3199.4375 115.1184) 
(list 3125.415 115.8684) 
(list 3125.415 115.6914) 
(list 3199.4375 115.0414)))
(apply 'command (append '("pline") coords '("c")))
(setq currobj (ssadd (entlast) currobj))
(setq coords (list 
(list 3199.4375 114.8984) 
(list 3125.415 115.5484) 
(list 3125.415 115.3714) 
(list 3199.4375 114.8214)))
(apply 'command (append '("pline") coords '("c")))
(setq currobj (ssadd (entlast) currobj))
(setq coords (list 
(list 3199.4375 114.6784) 
(list 3125.415 115.2284) 
(list 3125.415 115.0514) 
(list 3199.4375 114.6014)))
(apply 'command (append '("pline") coords '("c")))
(setq currobj (ssadd (entlast) currobj))
(setq coords (list 
(list 3199.4375 114.4584) 
(list 3125.415 114.9084) 
(list 3125.415 114.7314) 
(list 3199.4375 114.3814)))
(apply 'command (append '("pline") coords '("c")))
(setq currobj (ssadd (entlast) currobj))
(setq coords (list 
(list 3199.4375 114.2384) 
(list 3125.415 114.5884) 
(list 3125.415 114.4114) 
(list 3199.4375 114.1614)))
(apply 'command (append '("pline") coords '("c")))
(setq currobj (ssadd (entlast) currobj))
(setq coords (list 
(list 3199.4375 114.0184) 
(list 3125.415 114.2684) 
(list 3125.415 114.0914) 
(list 3199.4375 113.9414)))
(apply 'command (append '("pline") coords '("c")))
(setq currobj (ssadd (entlast) currobj))
(setq coords (list 
(list 3199.4375 113.7984) 
(list 3125.415 113.9484) 
(list 3125.415 113.7714) 
(list 3199.4375 113.7214)))
(apply 'command (append '("pline") coords '("c")))
(setq currobj (ssadd (entlast) currobj))
(setq coords (list 
(list 3199.4375 113.5784) 
(list 3125.415 113.6284) 
(list 3125.415 113.4514) 
(list 3199.4375 113.5014)))
(apply 'command (append '("pline") coords '("c")))
(setq currobj (ssadd (entlast) currobj))
(setq coords (list 
(list 3199.4375 113.3584) 
(list 3125.415 113.3084) 
(list 3125.415 113.1314) 
(list 3199.4375 113.2814)))
(apply 'command (append '("pline") coords '("c")))
(setq currobj (ssadd (entlast) currobj))
(setq coords (list 
(list 3199.4375 113.1384) 
(list 3125.415 112.9884) 
(list 3125.415 112.8114) 
(list 3199.4375 113.0614)))
(apply 'command (append '("pline") coords '("c")))
(setq currobj (ssadd (entlast) currobj))
(setq coords (list 
(list 3199.4375 112.9184) 
(list 3125.415 112.6684) 
(list 3125.415 112.4914) 
(list 3199.4375 112.8414)))
(apply 'command (append '("pline") coords '("c")))
(setq currobj (ssadd (entlast) currobj))
(setq coords (list 
(list 3199.4375 112.6984) 
(list 3125.415 112.3484) 
(list 3125.415 112.1714) 
(list 3199.4375 112.6214)))
(apply 'command (append '("pline") coords '("c")))
(setq currobj (ssadd (entlast) currobj))
(setq coords (list 
(list 3199.4375 112.4784) 
(list 3125.415 112.0284) 
(list 3125.415 111.8514) 
(list 3199.4375 112.4014)))
(apply 'command (append '("pline") coords '("c")))
(setq currobj (ssadd (entlast) currobj))
(setq coords (list 
(list 3199.4375 112.2584) 
(list 3125.415 111.7084) 
(list 3125.415 111.5314) 
(list 3199.4375 112.1814)))
(apply 'command (append '("pline") coords '("c")))
(setq currobj (ssadd (entlast) currobj))
(setq coords (list 
(list 3199.4375 112.0384) 
(list 3125.415 111.3884) 
(list 3125.415 111.2114) 
(list 3199.4375 111.9614)))
(apply 'command (append '("pline") coords '("c")))
(setq currobj (ssadd (entlast) currobj))
(command "_layer" "set" "nitride" "")
(command "_layer" "set" "text" "")
(command "_circle" "3199.0625,100.8184" "0.075")
(command "_circle" "3199.0625,101.1184" "0.075")
(command "_circle" "3199.0625,101.4184" "0.075")
(command "_circle" "3199.0625,101.7184" "0.075")
(command "_circle" "3199.0625,102.0184" "0.075")
(command "_circle" "3198.7625,100.8184" "0.075")
(command "_circle" "3198.7625,101.1184" "0.075")
(command "_circle" "3198.7625,101.4184" "0.075")
(command "_circle" "3198.7625,101.7184" "0.075")
(command "_circle" "3198.7625,102.0184" "0.075")
(command "_circle" "3198.4625,100.8184" "0.075")
(command "_circle" "3198.4625,101.1184" "0.075")
(command "_circle" "3198.4625,101.4184" "0.075")
(command "_circle" "3198.4625,101.7184" "0.075")
(command "_circle" "3198.4625,102.0184" "0.075")
(command "_circle" "3198.1625,100.8184" "0.075")
(command "_circle" "3198.1625,101.1184" "0.075")
(command "_circle" "3198.1625,101.4184" "0.075")
(command "_circle" "3198.1625,101.7184" "0.075")
(command "_circle" "3198.1625,102.0184" "0.075")
(command "_circle" "3197.8625,100.8184" "0.075")
(command "_circle" "3197.8625,101.1184" "0.075")
(command "_circle" "3197.8625,101.4184" "0.075")
(command "_circle" "3197.8625,101.7184" "0.075")
(command "_circle" "3197.8625,102.0184" "0.075")
(command "_layer" "set" "nitride" "")
(setq coords (list 
(list 3200.2625 126.2614) 
(list 3200.2625 241.9061) 
(list 3199.7375 241.9061) 
(list 3199.7375 126.2614)))
(apply 'command (append '("pline") coords '("c")))
(setq currobj (ssadd (entlast) currobj))
(command "_layer" "set" "prebias" "")
(command "_rectangle" "3199.7375,126.2614" "3200.2625,241.9061")
(setq currobj (ssadd (entlast) currobj))
(command "_layer" "set" "nitride" "")
(setq coords (list 
(list 3200.2625 241.9061) 
(list 3200.5625 251.9061) 
(list 3200.5625 251.9061) 
(list 3200.5625 252.9061) 
(list 3274.585 252.1561) 
(list 3274.585 257.0991) 
(list 3200.5625 256.3491) 
(list 3200.5625 257.3491) 
(list 3200.5625 257.3491) 
(list 3200.2625 267.3491) 
(list 3199.7375 267.3491) 
(list 3199.4375 257.3491) 
(list 3199.4375 257.3491) 
(list 3199.4375 256.3491) 
(list 3125.415 257.0991) 
(list 3125.415 252.1561) 
(list 3199.4375 252.9061) 
(list 3199.4375 251.9061) 
(list 3199.4375 251.9061) 
(list 3199.7375 241.9061)))
(apply 'command (append '("pline") coords '("c")))
(setq currobj (ssadd (entlast) currobj))
(command "_layer" "set" "prebias" "")
(setq coords (list 
(list 3199.4375 241.9061) 
(list 3199.4375 252.9061) 
(list 3125.415 252.1561) 
(list 3125.415 257.0991) 
(list 3199.4375 256.3491) 
(list 3199.4375 267.3491) 
(list 3200.5625 267.3491) 
(list 3200.5625 256.3491) 
(list 3274.585 257.0991) 
(list 3274.585 252.1561) 
(list 3200.5625 252.9061) 
(list 3200.5625 241.9061)))
(apply 'command (append '("pline") coords '("c")))
(setq currobj (ssadd (entlast) currobj))
(command "_layer" "set" "nitride" "")
(command "_layer" "set" "fda1" "")
(setq coords (list 
(list 3200.5625 253.0491) 
(list 3274.585 252.2991) 
(list 3274.585 252.4761) 
(list 3200.5625 253.1261)))
(apply 'command (append '("pline") coords '("c")))
(setq currobj (ssadd (entlast) currobj))
(setq coords (list 
(list 3200.5625 253.2691) 
(list 3274.585 252.6191) 
(list 3274.585 252.7961) 
(list 3200.5625 253.3461)))
(apply 'command (append '("pline") coords '("c")))
(setq currobj (ssadd (entlast) currobj))
(setq coords (list 
(list 3200.5625 253.4891) 
(list 3274.585 252.9391) 
(list 3274.585 253.1161) 
(list 3200.5625 253.5661)))
(apply 'command (append '("pline") coords '("c")))
(setq currobj (ssadd (entlast) currobj))
(setq coords (list 
(list 3200.5625 253.7091) 
(list 3274.585 253.2591) 
(list 3274.585 253.4361) 
(list 3200.5625 253.7861)))
(apply 'command (append '("pline") coords '("c")))
(setq currobj (ssadd (entlast) currobj))
(setq coords (list 
(list 3200.5625 253.9291) 
(list 3274.585 253.5791) 
(list 3274.585 253.7561) 
(list 3200.5625 254.0061)))
(apply 'command (append '("pline") coords '("c")))
(setq currobj (ssadd (entlast) currobj))
(setq coords (list 
(list 3200.5625 254.1491) 
(list 3274.585 253.8991) 
(list 3274.585 254.0761) 
(list 3200.5625 254.2261)))
(apply 'command (append '("pline") coords '("c")))
(setq currobj (ssadd (entlast) currobj))
(setq coords (list 
(list 3200.5625 254.3691) 
(list 3274.585 254.2191) 
(list 3274.585 254.3961) 
(list 3200.5625 254.4461)))
(apply 'command (append '("pline") coords '("c")))
(setq currobj (ssadd (entlast) currobj))
(setq coords (list 
(list 3200.5625 254.5891) 
(list 3274.585 254.5391) 
(list 3274.585 254.7161) 
(list 3200.5625 254.6661)))
(apply 'command (append '("pline") coords '("c")))
(setq currobj (ssadd (entlast) currobj))
(setq coords (list 
(list 3200.5625 254.8091) 
(list 3274.585 254.8591) 
(list 3274.585 255.0361) 
(list 3200.5625 254.8861)))
(apply 'command (append '("pline") coords '("c")))
(setq currobj (ssadd (entlast) currobj))
(setq coords (list 
(list 3200.5625 255.0291) 
(list 3274.585 255.1791) 
(list 3274.585 255.3561) 
(list 3200.5625 255.1061)))
(apply 'command (append '("pline") coords '("c")))
(setq currobj (ssadd (entlast) currobj))
(setq coords (list 
(list 3200.5625 255.2491) 
(list 3274.585 255.4991) 
(list 3274.585 255.6761) 
(list 3200.5625 255.3261)))
(apply 'command (append '("pline") coords '("c")))
(setq currobj (ssadd (entlast) currobj))
(setq coords (list 
(list 3200.5625 255.4691) 
(list 3274.585 255.8191) 
(list 3274.585 255.9961) 
(list 3200.5625 255.5461)))
(apply 'command (append '("pline") coords '("c")))
(setq currobj (ssadd (entlast) currobj))
(setq coords (list 
(list 3200.5625 255.6891) 
(list 3274.585 256.1391) 
(list 3274.585 256.3161) 
(list 3200.5625 255.7661)))
(apply 'command (append '("pline") coords '("c")))
(setq currobj (ssadd (entlast) currobj))
(setq coords (list 
(list 3200.5625 255.9091) 
(list 3274.585 256.4591) 
(list 3274.585 256.6361) 
(list 3200.5625 255.9861)))
(apply 'command (append '("pline") coords '("c")))
(setq currobj (ssadd (entlast) currobj))
(setq coords (list 
(list 3200.5625 256.1291) 
(list 3274.585 256.7791) 
(list 3274.585 256.9561) 
(list 3200.5625 256.2061)))
(apply 'command (append '("pline") coords '("c")))
(setq currobj (ssadd (entlast) currobj))
(setq coords (list 
(list 3199.4375 256.2061) 
(list 3125.415 256.9561) 
(list 3125.415 256.7791) 
(list 3199.4375 256.1291)))
(apply 'command (append '("pline") coords '("c")))
(setq currobj (ssadd (entlast) currobj))
(setq coords (list 
(list 3199.4375 255.9861) 
(list 3125.415 256.6361) 
(list 3125.415 256.4591) 
(list 3199.4375 255.9091)))
(apply 'command (append '("pline") coords '("c")))
(setq currobj (ssadd (entlast) currobj))
(setq coords (list 
(list 3199.4375 255.7661) 
(list 3125.415 256.3161) 
(list 3125.415 256.1391) 
(list 3199.4375 255.6891)))
(apply 'command (append '("pline") coords '("c")))
(setq currobj (ssadd (entlast) currobj))
(setq coords (list 
(list 3199.4375 255.5461) 
(list 3125.415 255.9961) 
(list 3125.415 255.8191) 
(list 3199.4375 255.4691)))
(apply 'command (append '("pline") coords '("c")))
(setq currobj (ssadd (entlast) currobj))
(setq coords (list 
(list 3199.4375 255.3261) 
(list 3125.415 255.6761) 
(list 3125.415 255.4991) 
(list 3199.4375 255.2491)))
(apply 'command (append '("pline") coords '("c")))
(setq currobj (ssadd (entlast) currobj))
(setq coords (list 
(list 3199.4375 255.1061) 
(list 3125.415 255.3561) 
(list 3125.415 255.1791) 
(list 3199.4375 255.0291)))
(apply 'command (append '("pline") coords '("c")))
(setq currobj (ssadd (entlast) currobj))
(setq coords (list 
(list 3199.4375 254.8861) 
(list 3125.415 255.0361) 
(list 3125.415 254.8591) 
(list 3199.4375 254.8091)))
(apply 'command (append '("pline") coords '("c")))
(setq currobj (ssadd (entlast) currobj))
(setq coords (list 
(list 3199.4375 254.6661) 
(list 3125.415 254.7161) 
(list 3125.415 254.5391) 
(list 3199.4375 254.5891)))
(apply 'command (append '("pline") coords '("c")))
(setq currobj (ssadd (entlast) currobj))
(setq coords (list 
(list 3199.4375 254.4461) 
(list 3125.415 254.3961) 
(list 3125.415 254.2191) 
(list 3199.4375 254.3691)))
(apply 'command (append '("pline") coords '("c")))
(setq currobj (ssadd (entlast) currobj))
(setq coords (list 
(list 3199.4375 254.2261) 
(list 3125.415 254.0761) 
(list 3125.415 253.8991) 
(list 3199.4375 254.1491)))
(apply 'command (append '("pline") coords '("c")))
(setq currobj (ssadd (entlast) currobj))
(setq coords (list 
(list 3199.4375 254.0061) 
(list 3125.415 253.7561) 
(list 3125.415 253.5791) 
(list 3199.4375 253.9291)))
(apply 'command (append '("pline") coords '("c")))
(setq currobj (ssadd (entlast) currobj))
(setq coords (list 
(list 3199.4375 253.7861) 
(list 3125.415 253.4361) 
(list 3125.415 253.2591) 
(list 3199.4375 253.7091)))
(apply 'command (append '("pline") coords '("c")))
(setq currobj (ssadd (entlast) currobj))
(setq coords (list 
(list 3199.4375 253.5661) 
(list 3125.415 253.1161) 
(list 3125.415 252.9391) 
(list 3199.4375 253.4891)))
(apply 'command (append '("pline") coords '("c")))
(setq currobj (ssadd (entlast) currobj))
(setq coords (list 
(list 3199.4375 253.3461) 
(list 3125.415 252.7961) 
(list 3125.415 252.6191) 
(list 3199.4375 253.2691)))
(apply 'command (append '("pline") coords '("c")))
(setq currobj (ssadd (entlast) currobj))
(setq coords (list 
(list 3199.4375 253.1261) 
(list 3125.415 252.4761) 
(list 3125.415 252.2991) 
(list 3199.4375 253.0491)))
(apply 'command (append '("pline") coords '("c")))
(setq currobj (ssadd (entlast) currobj))
(command "_layer" "set" "nitride" "")
(command "_layer" "set" "text" "")
(command "_circle" "3199.0625,241.9061" "0.075")
(command "_circle" "3199.0625,242.2061" "0.075")
(command "_circle" "3199.0625,242.5061" "0.075")
(command "_circle" "3199.0625,242.8061" "0.075")
(command "_circle" "3199.0625,243.1061" "0.075")
(command "_circle" "3198.7625,241.9061" "0.075")
(command "_circle" "3198.7625,242.2061" "0.075")
(command "_circle" "3198.7625,242.5061" "0.075")
(command "_circle" "3198.7625,242.8061" "0.075")
(command "_circle" "3198.7625,243.1061" "0.075")
(command "_circle" "3198.4625,241.9061" "0.075")
(command "_circle" "3198.4625,242.2061" "0.075")
(command "_circle" "3198.4625,242.5061" "0.075")
(command "_circle" "3198.4625,242.8061" "0.075")
(command "_circle" "3198.4625,243.1061" "0.075")
(command "_circle" "3198.1625,241.9061" "0.075")
(command "_circle" "3198.1625,242.2061" "0.075")
(command "_circle" "3198.1625,242.5061" "0.075")
(command "_circle" "3198.1625,242.8061" "0.075")
(command "_circle" "3198.1625,243.1061" "0.075")
(command "_circle" "3197.8625,241.9061" "0.075")
(command "_circle" "3197.8625,242.2061" "0.075")
(command "_circle" "3197.8625,242.5061" "0.075")
(command "_circle" "3197.8625,242.8061" "0.075")
(command "_circle" "3197.8625,243.1061" "0.075")
(command "_layer" "set" "nitride" "")
(setq coords (list 
(list 3200.2625 267.3491) 
(list 3200.2625 382.9939) 
(list 3199.7375 382.9939) 
(list 3199.7375 267.3491)))
(apply 'command (append '("pline") coords '("c")))
(setq currobj (ssadd (entlast) currobj))
(command "_layer" "set" "prebias" "")
(command "_rectangle" "3199.7375,267.3491" "3200.2625,382.9939")
(setq currobj (ssadd (entlast) currobj))
(command "_layer" "set" "nitride" "")
(setq coords (list 
(list 3200.2625 382.9939) 
(list 3200.5625 392.9939) 
(list 3200.5625 392.9939) 
(list 3200.5625 393.9939) 
(list 3274.585 393.2439) 
(list 3274.585 398.1869) 
(list 3200.5625 397.4369) 
(list 3200.5625 398.4369) 
(list 3200.5625 398.4369) 
(list 3200.2625 408.4369) 
(list 3199.7375 408.4369) 
(list 3199.4375 398.4369) 
(list 3199.4375 398.4369) 
(list 3199.4375 397.4369) 
(list 3125.415 398.1869) 
(list 3125.415 393.2439) 
(list 3199.4375 393.9939) 
(list 3199.4375 392.9939) 
(list 3199.4375 392.9939) 
(list 3199.7375 382.9939)))
(apply 'command (append '("pline") coords '("c")))
(setq currobj (ssadd (entlast) currobj))
(command "_layer" "set" "prebias" "")
(setq coords (list 
(list 3199.4375 382.9939) 
(list 3199.4375 393.9939) 
(list 3125.415 393.2439) 
(list 3125.415 398.1869) 
(list 3199.4375 397.4369) 
(list 3199.4375 408.4369) 
(list 3200.5625 408.4369) 
(list 3200.5625 397.4369) 
(list 3274.585 398.1869) 
(list 3274.585 393.2439) 
(list 3200.5625 393.9939) 
(list 3200.5625 382.9939)))
(apply 'command (append '("pline") coords '("c")))
(setq currobj (ssadd (entlast) currobj))
(command "_layer" "set" "nitride" "")
(command "_layer" "set" "fda1" "")
(setq coords (list 
(list 3200.5625 394.1369) 
(list 3274.585 393.3869) 
(list 3274.585 393.5639) 
(list 3200.5625 394.2139)))
(apply 'command (append '("pline") coords '("c")))
(setq currobj (ssadd (entlast) currobj))
(setq coords (list 
(list 3200.5625 394.3569) 
(list 3274.585 393.7069) 
(list 3274.585 393.8839) 
(list 3200.5625 394.4339)))
(apply 'command (append '("pline") coords '("c")))
(setq currobj (ssadd (entlast) currobj))
(setq coords (list 
(list 3200.5625 394.5769) 
(list 3274.585 394.0269) 
(list 3274.585 394.2039) 
(list 3200.5625 394.6539)))
(apply 'command (append '("pline") coords '("c")))
(setq currobj (ssadd (entlast) currobj))
(setq coords (list 
(list 3200.5625 394.7969) 
(list 3274.585 394.3469) 
(list 3274.585 394.5239) 
(list 3200.5625 394.8739)))
(apply 'command (append '("pline") coords '("c")))
(setq currobj (ssadd (entlast) currobj))
(setq coords (list 
(list 3200.5625 395.0169) 
(list 3274.585 394.6669) 
(list 3274.585 394.8439) 
(list 3200.5625 395.0939)))
(apply 'command (append '("pline") coords '("c")))
(setq currobj (ssadd (entlast) currobj))
(setq coords (list 
(list 3200.5625 395.2369) 
(list 3274.585 394.9869) 
(list 3274.585 395.1639) 
(list 3200.5625 395.3139)))
(apply 'command (append '("pline") coords '("c")))
(setq currobj (ssadd (entlast) currobj))
(setq coords (list 
(list 3200.5625 395.4569) 
(list 3274.585 395.3069) 
(list 3274.585 395.4839) 
(list 3200.5625 395.5339)))
(apply 'command (append '("pline") coords '("c")))
(setq currobj (ssadd (entlast) currobj))
(setq coords (list 
(list 3200.5625 395.6769) 
(list 3274.585 395.6269) 
(list 3274.585 395.8039) 
(list 3200.5625 395.7539)))
(apply 'command (append '("pline") coords '("c")))
(setq currobj (ssadd (entlast) currobj))
(setq coords (list 
(list 3200.5625 395.8969) 
(list 3274.585 395.9469) 
(list 3274.585 396.1239) 
(list 3200.5625 395.9739)))
(apply 'command (append '("pline") coords '("c")))
(setq currobj (ssadd (entlast) currobj))
(setq coords (list 
(list 3200.5625 396.1169) 
(list 3274.585 396.2669) 
(list 3274.585 396.4439) 
(list 3200.5625 396.1939)))
(apply 'command (append '("pline") coords '("c")))
(setq currobj (ssadd (entlast) currobj))
(setq coords (list 
(list 3200.5625 396.3369) 
(list 3274.585 396.5869) 
(list 3274.585 396.7639) 
(list 3200.5625 396.4139)))
(apply 'command (append '("pline") coords '("c")))
(setq currobj (ssadd (entlast) currobj))
(setq coords (list 
(list 3200.5625 396.5569) 
(list 3274.585 396.9069) 
(list 3274.585 397.0839) 
(list 3200.5625 396.6339)))
(apply 'command (append '("pline") coords '("c")))
(setq currobj (ssadd (entlast) currobj))
(setq coords (list 
(list 3200.5625 396.7769) 
(list 3274.585 397.2269) 
(list 3274.585 397.4039) 
(list 3200.5625 396.8539)))
(apply 'command (append '("pline") coords '("c")))
(setq currobj (ssadd (entlast) currobj))
(setq coords (list 
(list 3200.5625 396.9969) 
(list 3274.585 397.5469) 
(list 3274.585 397.7239) 
(list 3200.5625 397.0739)))
(apply 'command (append '("pline") coords '("c")))
(setq currobj (ssadd (entlast) currobj))
(setq coords (list 
(list 3200.5625 397.2169) 
(list 3274.585 397.8669) 
(list 3274.585 398.0439) 
(list 3200.5625 397.2939)))
(apply 'command (append '("pline") coords '("c")))
(setq currobj (ssadd (entlast) currobj))
(setq coords (list 
(list 3199.4375 397.2939) 
(list 3125.415 398.0439) 
(list 3125.415 397.8669) 
(list 3199.4375 397.2169)))
(apply 'command (append '("pline") coords '("c")))
(setq currobj (ssadd (entlast) currobj))
(setq coords (list 
(list 3199.4375 397.0739) 
(list 3125.415 397.7239) 
(list 3125.415 397.5469) 
(list 3199.4375 396.9969)))
(apply 'command (append '("pline") coords '("c")))
(setq currobj (ssadd (entlast) currobj))
(setq coords (list 
(list 3199.4375 396.8539) 
(list 3125.415 397.4039) 
(list 3125.415 397.2269) 
(list 3199.4375 396.7769)))
(apply 'command (append '("pline") coords '("c")))
(setq currobj (ssadd (entlast) currobj))
(setq coords (list 
(list 3199.4375 396.6339) 
(list 3125.415 397.0839) 
(list 3125.415 396.9069) 
(list 3199.4375 396.5569)))
(apply 'command (append '("pline") coords '("c")))
(setq currobj (ssadd (entlast) currobj))
(setq coords (list 
(list 3199.4375 396.4139) 
(list 3125.415 396.7639) 
(list 3125.415 396.5869) 
(list 3199.4375 396.3369)))
(apply 'command (append '("pline") coords '("c")))
(setq currobj (ssadd (entlast) currobj))
(setq coords (list 
(list 3199.4375 396.1939) 
(list 3125.415 396.4439) 
(list 3125.415 396.2669) 
(list 3199.4375 396.1169)))
(apply 'command (append '("pline") coords '("c")))
(setq currobj (ssadd (entlast) currobj))
(setq coords (list 
(list 3199.4375 395.9739) 
(list 3125.415 396.1239) 
(list 3125.415 395.9469) 
(list 3199.4375 395.8969)))
(apply 'command (append '("pline") coords '("c")))
(setq currobj (ssadd (entlast) currobj))
(setq coords (list 
(list 3199.4375 395.7539) 
(list 3125.415 395.8039) 
(list 3125.415 395.6269) 
(list 3199.4375 395.6769)))
(apply 'command (append '("pline") coords '("c")))
(setq currobj (ssadd (entlast) currobj))
(setq coords (list 
(list 3199.4375 395.5339) 
(list 3125.415 395.4839) 
(list 3125.415 395.3069) 
(list 3199.4375 395.4569)))
(apply 'command (append '("pline") coords '("c")))
(setq currobj (ssadd (entlast) currobj))
(setq coords (list 
(list 3199.4375 395.3139) 
(list 3125.415 395.1639) 
(list 3125.415 394.9869) 
(list 3199.4375 395.2369)))
(apply 'command (append '("pline") coords '("c")))
(setq currobj (ssadd (entlast) currobj))
(setq coords (list 
(list 3199.4375 395.0939) 
(list 3125.415 394.8439) 
(list 3125.415 394.6669) 
(list 3199.4375 395.0169)))
(apply 'command (append '("pline") coords '("c")))
(setq currobj (ssadd (entlast) currobj))
(setq coords (list 
(list 3199.4375 394.8739) 
(list 3125.415 394.5239) 
(list 3125.415 394.3469) 
(list 3199.4375 394.7969)))
(apply 'command (append '("pline") coords '("c")))
(setq currobj (ssadd (entlast) currobj))
(setq coords (list 
(list 3199.4375 394.6539) 
(list 3125.415 394.2039) 
(list 3125.415 394.0269) 
(list 3199.4375 394.5769)))
(apply 'command (append '("pline") coords '("c")))
(setq currobj (ssadd (entlast) currobj))
(setq coords (list 
(list 3199.4375 394.4339) 
(list 3125.415 393.8839) 
(list 3125.415 393.7069) 
(list 3199.4375 394.3569)))
(apply 'command (append '("pline") coords '("c")))
(setq currobj (ssadd (entlast) currobj))
(setq coords (list 
(list 3199.4375 394.2139) 
(list 3125.415 393.5639) 
(list 3125.415 393.3869) 
(list 3199.4375 394.1369)))
(apply 'command (append '("pline") coords '("c")))
(setq currobj (ssadd (entlast) currobj))
(command "_layer" "set" "nitride" "")
(command "_layer" "set" "text" "")
(command "_circle" "3199.0625,382.9939" "0.075")
(command "_circle" "3199.0625,383.2939" "0.075")
(command "_circle" "3199.0625,383.5939" "0.075")
(command "_circle" "3199.0625,383.8939" "0.075")
(command "_circle" "3199.0625,384.1939" "0.075")
(command "_circle" "3198.7625,382.9939" "0.075")
(command "_circle" "3198.7625,383.2939" "0.075")
(command "_circle" "3198.7625,383.5939" "0.075")
(command "_circle" "3198.7625,383.8939" "0.075")
(command "_circle" "3198.7625,384.1939" "0.075")
(command "_circle" "3198.4625,382.9939" "0.075")
(command "_circle" "3198.4625,383.2939" "0.075")
(command "_circle" "3198.4625,383.5939" "0.075")
(command "_circle" "3198.4625,383.8939" "0.075")
(command "_circle" "3198.4625,384.1939" "0.075")
(command "_circle" "3198.1625,382.9939" "0.075")
(command "_circle" "3198.1625,383.2939" "0.075")
(command "_circle" "3198.1625,383.5939" "0.075")
(command "_circle" "3198.1625,383.8939" "0.075")
(command "_circle" "3198.1625,384.1939" "0.075")
(command "_circle" "3197.8625,382.9939" "0.075")
(command "_circle" "3197.8625,383.2939" "0.075")
(command "_circle" "3197.8625,383.5939" "0.075")
(command "_circle" "3197.8625,383.8939" "0.075")
(command "_circle" "3197.8625,384.1939" "0.075")
(command "_layer" "set" "nitride" "")
(setq coords (list 
(list 3200.2625 408.4369) 
(list 3200.2625 524.0816) 
(list 3199.7375 524.0816) 
(list 3199.7375 408.4369)))
(apply 'command (append '("pline") coords '("c")))
(setq currobj (ssadd (entlast) currobj))
(command "_layer" "set" "prebias" "")
(command "_rectangle" "3199.7375,408.4369" "3200.2625,524.0816")
(setq currobj (ssadd (entlast) currobj))
(command "_layer" "set" "nitride" "")
(setq coords (list 
(list 3200.2625 524.0816) 
(list 3200.5625 534.0816) 
(list 3200.5625 534.0816) 
(list 3200.5625 535.0816) 
(list 3274.585 534.3316) 
(list 3274.585 539.2746) 
(list 3200.5625 538.5246) 
(list 3200.5625 539.5246) 
(list 3200.5625 539.5246) 
(list 3200.2625 549.5246) 
(list 3199.7375 549.5246) 
(list 3199.4375 539.5246) 
(list 3199.4375 539.5246) 
(list 3199.4375 538.5246) 
(list 3125.415 539.2746) 
(list 3125.415 534.3316) 
(list 3199.4375 535.0816) 
(list 3199.4375 534.0816) 
(list 3199.4375 534.0816) 
(list 3199.7375 524.0816)))
(apply 'command (append '("pline") coords '("c")))
(setq currobj (ssadd (entlast) currobj))
(command "_layer" "set" "prebias" "")
(setq coords (list 
(list 3199.4375 524.0816) 
(list 3199.4375 535.0816) 
(list 3125.415 534.3316) 
(list 3125.415 539.2746) 
(list 3199.4375 538.5246) 
(list 3199.4375 549.5246) 
(list 3200.5625 549.5246) 
(list 3200.5625 538.5246) 
(list 3274.585 539.2746) 
(list 3274.585 534.3316) 
(list 3200.5625 535.0816) 
(list 3200.5625 524.0816)))
(apply 'command (append '("pline") coords '("c")))
(setq currobj (ssadd (entlast) currobj))
(command "_layer" "set" "nitride" "")
(command "_layer" "set" "fda1" "")
(setq coords (list 
(list 3200.5625 535.2246) 
(list 3274.585 534.4746) 
(list 3274.585 534.6516) 
(list 3200.5625 535.3016)))
(apply 'command (append '("pline") coords '("c")))
(setq currobj (ssadd (entlast) currobj))
(setq coords (list 
(list 3200.5625 535.4446) 
(list 3274.585 534.7946) 
(list 3274.585 534.9716) 
(list 3200.5625 535.5216)))
(apply 'command (append '("pline") coords '("c")))
(setq currobj (ssadd (entlast) currobj))
(setq coords (list 
(list 3200.5625 535.6646) 
(list 3274.585 535.1146) 
(list 3274.585 535.2916) 
(list 3200.5625 535.7416)))
(apply 'command (append '("pline") coords '("c")))
(setq currobj (ssadd (entlast) currobj))
(setq coords (list 
(list 3200.5625 535.8846) 
(list 3274.585 535.4346) 
(list 3274.585 535.6116) 
(list 3200.5625 535.9616)))
(apply 'command (append '("pline") coords '("c")))
(setq currobj (ssadd (entlast) currobj))
(setq coords (list 
(list 3200.5625 536.1046) 
(list 3274.585 535.7546) 
(list 3274.585 535.9316) 
(list 3200.5625 536.1816)))
(apply 'command (append '("pline") coords '("c")))
(setq currobj (ssadd (entlast) currobj))
(setq coords (list 
(list 3200.5625 536.3246) 
(list 3274.585 536.0746) 
(list 3274.585 536.2516) 
(list 3200.5625 536.4016)))
(apply 'command (append '("pline") coords '("c")))
(setq currobj (ssadd (entlast) currobj))
(setq coords (list 
(list 3200.5625 536.5446) 
(list 3274.585 536.3946) 
(list 3274.585 536.5716) 
(list 3200.5625 536.6216)))
(apply 'command (append '("pline") coords '("c")))
(setq currobj (ssadd (entlast) currobj))
(setq coords (list 
(list 3200.5625 536.7646) 
(list 3274.585 536.7146) 
(list 3274.585 536.8916) 
(list 3200.5625 536.8416)))
(apply 'command (append '("pline") coords '("c")))
(setq currobj (ssadd (entlast) currobj))
(setq coords (list 
(list 3200.5625 536.9846) 
(list 3274.585 537.0346) 
(list 3274.585 537.2116) 
(list 3200.5625 537.0616)))
(apply 'command (append '("pline") coords '("c")))
(setq currobj (ssadd (entlast) currobj))
(setq coords (list 
(list 3200.5625 537.2046) 
(list 3274.585 537.3546) 
(list 3274.585 537.5316) 
(list 3200.5625 537.2816)))
(apply 'command (append '("pline") coords '("c")))
(setq currobj (ssadd (entlast) currobj))
(setq coords (list 
(list 3200.5625 537.4246) 
(list 3274.585 537.6746) 
(list 3274.585 537.8516) 
(list 3200.5625 537.5016)))
(apply 'command (append '("pline") coords '("c")))
(setq currobj (ssadd (entlast) currobj))
(setq coords (list 
(list 3200.5625 537.6446) 
(list 3274.585 537.9946) 
(list 3274.585 538.1716) 
(list 3200.5625 537.7216)))
(apply 'command (append '("pline") coords '("c")))
(setq currobj (ssadd (entlast) currobj))
(setq coords (list 
(list 3200.5625 537.8646) 
(list 3274.585 538.3146) 
(list 3274.585 538.4916) 
(list 3200.5625 537.9416)))
(apply 'command (append '("pline") coords '("c")))
(setq currobj (ssadd (entlast) currobj))
(setq coords (list 
(list 3200.5625 538.0846) 
(list 3274.585 538.6346) 
(list 3274.585 538.8116) 
(list 3200.5625 538.1616)))
(apply 'command (append '("pline") coords '("c")))
(setq currobj (ssadd (entlast) currobj))
(setq coords (list 
(list 3200.5625 538.3046) 
(list 3274.585 538.9546) 
(list 3274.585 539.1316) 
(list 3200.5625 538.3816)))
(apply 'command (append '("pline") coords '("c")))
(setq currobj (ssadd (entlast) currobj))
(setq coords (list 
(list 3199.4375 538.3816) 
(list 3125.415 539.1316) 
(list 3125.415 538.9546) 
(list 3199.4375 538.3046)))
(apply 'command (append '("pline") coords '("c")))
(setq currobj (ssadd (entlast) currobj))
(setq coords (list 
(list 3199.4375 538.1616) 
(list 3125.415 538.8116) 
(list 3125.415 538.6346) 
(list 3199.4375 538.0846)))
(apply 'command (append '("pline") coords '("c")))
(setq currobj (ssadd (entlast) currobj))
(setq coords (list 
(list 3199.4375 537.9416) 
(list 3125.415 538.4916) 
(list 3125.415 538.3146) 
(list 3199.4375 537.8646)))
(apply 'command (append '("pline") coords '("c")))
(setq currobj (ssadd (entlast) currobj))
(setq coords (list 
(list 3199.4375 537.7216) 
(list 3125.415 538.1716) 
(list 3125.415 537.9946) 
(list 3199.4375 537.6446)))
(apply 'command (append '("pline") coords '("c")))
(setq currobj (ssadd (entlast) currobj))
(setq coords (list 
(list 3199.4375 537.5016) 
(list 3125.415 537.8516) 
(list 3125.415 537.6746) 
(list 3199.4375 537.4246)))
(apply 'command (append '("pline") coords '("c")))
(setq currobj (ssadd (entlast) currobj))
(setq coords (list 
(list 3199.4375 537.2816) 
(list 3125.415 537.5316) 
(list 3125.415 537.3546) 
(list 3199.4375 537.2046)))
(apply 'command (append '("pline") coords '("c")))
(setq currobj (ssadd (entlast) currobj))
(setq coords (list 
(list 3199.4375 537.0616) 
(list 3125.415 537.2116) 
(list 3125.415 537.0346) 
(list 3199.4375 536.9846)))
(apply 'command (append '("pline") coords '("c")))
(setq currobj (ssadd (entlast) currobj))
(setq coords (list 
(list 3199.4375 536.8416) 
(list 3125.415 536.8916) 
(list 3125.415 536.7146) 
(list 3199.4375 536.7646)))
(apply 'command (append '("pline") coords '("c")))
(setq currobj (ssadd (entlast) currobj))
(setq coords (list 
(list 3199.4375 536.6216) 
(list 3125.415 536.5716) 
(list 3125.415 536.3946) 
(list 3199.4375 536.5446)))
(apply 'command (append '("pline") coords '("c")))
(setq currobj (ssadd (entlast) currobj))
(setq coords (list 
(list 3199.4375 536.4016) 
(list 3125.415 536.2516) 
(list 3125.415 536.0746) 
(list 3199.4375 536.3246)))
(apply 'command (append '("pline") coords '("c")))
(setq currobj (ssadd (entlast) currobj))
(setq coords (list 
(list 3199.4375 536.1816) 
(list 3125.415 535.9316) 
(list 3125.415 535.7546) 
(list 3199.4375 536.1046)))
(apply 'command (append '("pline") coords '("c")))
(setq currobj (ssadd (entlast) currobj))
(setq coords (list 
(list 3199.4375 535.9616) 
(list 3125.415 535.6116) 
(list 3125.415 535.4346) 
(list 3199.4375 535.8846)))
(apply 'command (append '("pline") coords '("c")))
(setq currobj (ssadd (entlast) currobj))
(setq coords (list 
(list 3199.4375 535.7416) 
(list 3125.415 535.2916) 
(list 3125.415 535.1146) 
(list 3199.4375 535.6646)))
(apply 'command (append '("pline") coords '("c")))
(setq currobj (ssadd (entlast) currobj))
(setq coords (list 
(list 3199.4375 535.5216) 
(list 3125.415 534.9716) 
(list 3125.415 534.7946) 
(list 3199.4375 535.4446)))
(apply 'command (append '("pline") coords '("c")))
(setq currobj (ssadd (entlast) currobj))
(setq coords (list 
(list 3199.4375 535.3016) 
(list 3125.415 534.6516) 
(list 3125.415 534.4746) 
(list 3199.4375 535.2246)))
(apply 'command (append '("pline") coords '("c")))
(setq currobj (ssadd (entlast) currobj))
(command "_layer" "set" "nitride" "")
(command "_layer" "set" "text" "")
(command "_circle" "3199.0625,524.0816" "0.075")
(command "_circle" "3199.0625,524.3816" "0.075")
(command "_circle" "3199.0625,524.6816" "0.075")
(command "_circle" "3199.0625,524.9816" "0.075")
(command "_circle" "3199.0625,525.2816" "0.075")
(command "_circle" "3198.7625,524.0816" "0.075")
(command "_circle" "3198.7625,524.3816" "0.075")
(command "_circle" "3198.7625,524.6816" "0.075")
(command "_circle" "3198.7625,524.9816" "0.075")
(command "_circle" "3198.7625,525.2816" "0.075")
(command "_circle" "3198.4625,524.0816" "0.075")
(command "_circle" "3198.4625,524.3816" "0.075")
(command "_circle" "3198.4625,524.6816" "0.075")
(command "_circle" "3198.4625,524.9816" "0.075")
(command "_circle" "3198.4625,525.2816" "0.075")
(command "_circle" "3198.1625,524.0816" "0.075")
(command "_circle" "3198.1625,524.3816" "0.075")
(command "_circle" "3198.1625,524.6816" "0.075")
(command "_circle" "3198.1625,524.9816" "0.075")
(command "_circle" "3198.1625,525.2816" "0.075")
(command "_circle" "3197.8625,524.0816" "0.075")
(command "_circle" "3197.8625,524.3816" "0.075")
(command "_circle" "3197.8625,524.6816" "0.075")
(command "_circle" "3197.8625,524.9816" "0.075")
(command "_circle" "3197.8625,525.2816" "0.075")
(command "_layer" "set" "nitride" "")
(setq coords (list 
(list 3200.2625 549.5246) 
(list 3200.2625 665.1693) 
(list 3199.7375 665.1693) 
(list 3199.7375 549.5246)))
(apply 'command (append '("pline") coords '("c")))
(setq currobj (ssadd (entlast) currobj))
(command "_layer" "set" "prebias" "")
(command "_rectangle" "3199.7375,549.5246" "3200.2625,665.1693")
(setq currobj (ssadd (entlast) currobj))
(command "_layer" "set" "nitride" "")
(setq coords (list 
(list 3200.2625 665.1693) 
(list 3200.5625 675.1693) 
(list 3200.5625 675.1693) 
(list 3200.5625 676.1693) 
(list 3274.585 675.4193) 
(list 3274.585 680.3623) 
(list 3200.5625 679.6123) 
(list 3200.5625 680.6123) 
(list 3200.5625 680.6123) 
(list 3200.2625 690.6123) 
(list 3199.7375 690.6123) 
(list 3199.4375 680.6123) 
(list 3199.4375 680.6123) 
(list 3199.4375 679.6123) 
(list 3125.415 680.3623) 
(list 3125.415 675.4193) 
(list 3199.4375 676.1693) 
(list 3199.4375 675.1693) 
(list 3199.4375 675.1693) 
(list 3199.7375 665.1693)))
(apply 'command (append '("pline") coords '("c")))
(setq currobj (ssadd (entlast) currobj))
(command "_layer" "set" "prebias" "")
(setq coords (list 
(list 3199.4375 665.1693) 
(list 3199.4375 676.1693) 
(list 3125.415 675.4193) 
(list 3125.415 680.3623) 
(list 3199.4375 679.6123) 
(list 3199.4375 690.6123) 
(list 3200.5625 690.6123) 
(list 3200.5625 679.6123) 
(list 3274.585 680.3623) 
(list 3274.585 675.4193) 
(list 3200.5625 676.1693) 
(list 3200.5625 665.1693)))
(apply 'command (append '("pline") coords '("c")))
(setq currobj (ssadd (entlast) currobj))
(command "_layer" "set" "nitride" "")
(command "_layer" "set" "fda1" "")
(setq coords (list 
(list 3200.5625 676.3123) 
(list 3274.585 675.5623) 
(list 3274.585 675.7393) 
(list 3200.5625 676.3893)))
(apply 'command (append '("pline") coords '("c")))
(setq currobj (ssadd (entlast) currobj))
(setq coords (list 
(list 3200.5625 676.5323) 
(list 3274.585 675.8823) 
(list 3274.585 676.0593) 
(list 3200.5625 676.6093)))
(apply 'command (append '("pline") coords '("c")))
(setq currobj (ssadd (entlast) currobj))
(setq coords (list 
(list 3200.5625 676.7523) 
(list 3274.585 676.2023) 
(list 3274.585 676.3793) 
(list 3200.5625 676.8293)))
(apply 'command (append '("pline") coords '("c")))
(setq currobj (ssadd (entlast) currobj))
(setq coords (list 
(list 3200.5625 676.9723) 
(list 3274.585 676.5223) 
(list 3274.585 676.6993) 
(list 3200.5625 677.0493)))
(apply 'command (append '("pline") coords '("c")))
(setq currobj (ssadd (entlast) currobj))
(setq coords (list 
(list 3200.5625 677.1923) 
(list 3274.585 676.8423) 
(list 3274.585 677.0193) 
(list 3200.5625 677.2693)))
(apply 'command (append '("pline") coords '("c")))
(setq currobj (ssadd (entlast) currobj))
(setq coords (list 
(list 3200.5625 677.4123) 
(list 3274.585 677.1623) 
(list 3274.585 677.3393) 
(list 3200.5625 677.4893)))
(apply 'command (append '("pline") coords '("c")))
(setq currobj (ssadd (entlast) currobj))
(setq coords (list 
(list 3200.5625 677.6323) 
(list 3274.585 677.4823) 
(list 3274.585 677.6593) 
(list 3200.5625 677.7093)))
(apply 'command (append '("pline") coords '("c")))
(setq currobj (ssadd (entlast) currobj))
(setq coords (list 
(list 3200.5625 677.8523) 
(list 3274.585 677.8023) 
(list 3274.585 677.9793) 
(list 3200.5625 677.9293)))
(apply 'command (append '("pline") coords '("c")))
(setq currobj (ssadd (entlast) currobj))
(setq coords (list 
(list 3200.5625 678.0723) 
(list 3274.585 678.1223) 
(list 3274.585 678.2993) 
(list 3200.5625 678.1493)))
(apply 'command (append '("pline") coords '("c")))
(setq currobj (ssadd (entlast) currobj))
(setq coords (list 
(list 3200.5625 678.2923) 
(list 3274.585 678.4423) 
(list 3274.585 678.6193) 
(list 3200.5625 678.3693)))
(apply 'command (append '("pline") coords '("c")))
(setq currobj (ssadd (entlast) currobj))
(setq coords (list 
(list 3200.5625 678.5123) 
(list 3274.585 678.7623) 
(list 3274.585 678.9393) 
(list 3200.5625 678.5893)))
(apply 'command (append '("pline") coords '("c")))
(setq currobj (ssadd (entlast) currobj))
(setq coords (list 
(list 3200.5625 678.7323) 
(list 3274.585 679.0823) 
(list 3274.585 679.2593) 
(list 3200.5625 678.8093)))
(apply 'command (append '("pline") coords '("c")))
(setq currobj (ssadd (entlast) currobj))
(setq coords (list 
(list 3200.5625 678.9523) 
(list 3274.585 679.4023) 
(list 3274.585 679.5793) 
(list 3200.5625 679.0293)))
(apply 'command (append '("pline") coords '("c")))
(setq currobj (ssadd (entlast) currobj))
(setq coords (list 
(list 3200.5625 679.1723) 
(list 3274.585 679.7223) 
(list 3274.585 679.8993) 
(list 3200.5625 679.2493)))
(apply 'command (append '("pline") coords '("c")))
(setq currobj (ssadd (entlast) currobj))
(setq coords (list 
(list 3200.5625 679.3923) 
(list 3274.585 680.0423) 
(list 3274.585 680.2193) 
(list 3200.5625 679.4693)))
(apply 'command (append '("pline") coords '("c")))
(setq currobj (ssadd (entlast) currobj))
(setq coords (list 
(list 3199.4375 679.4693) 
(list 3125.415 680.2193) 
(list 3125.415 680.0423) 
(list 3199.4375 679.3923)))
(apply 'command (append '("pline") coords '("c")))
(setq currobj (ssadd (entlast) currobj))
(setq coords (list 
(list 3199.4375 679.2493) 
(list 3125.415 679.8993) 
(list 3125.415 679.7223) 
(list 3199.4375 679.1723)))
(apply 'command (append '("pline") coords '("c")))
(setq currobj (ssadd (entlast) currobj))
(setq coords (list 
(list 3199.4375 679.0293) 
(list 3125.415 679.5793) 
(list 3125.415 679.4023) 
(list 3199.4375 678.9523)))
(apply 'command (append '("pline") coords '("c")))
(setq currobj (ssadd (entlast) currobj))
(setq coords (list 
(list 3199.4375 678.8093) 
(list 3125.415 679.2593) 
(list 3125.415 679.0823) 
(list 3199.4375 678.7323)))
(apply 'command (append '("pline") coords '("c")))
(setq currobj (ssadd (entlast) currobj))
(setq coords (list 
(list 3199.4375 678.5893) 
(list 3125.415 678.9393) 
(list 3125.415 678.7623) 
(list 3199.4375 678.5123)))
(apply 'command (append '("pline") coords '("c")))
(setq currobj (ssadd (entlast) currobj))
(setq coords (list 
(list 3199.4375 678.3693) 
(list 3125.415 678.6193) 
(list 3125.415 678.4423) 
(list 3199.4375 678.2923)))
(apply 'command (append '("pline") coords '("c")))
(setq currobj (ssadd (entlast) currobj))
(setq coords (list 
(list 3199.4375 678.1493) 
(list 3125.415 678.2993) 
(list 3125.415 678.1223) 
(list 3199.4375 678.0723)))
(apply 'command (append '("pline") coords '("c")))
(setq currobj (ssadd (entlast) currobj))
(setq coords (list 
(list 3199.4375 677.9293) 
(list 3125.415 677.9793) 
(list 3125.415 677.8023) 
(list 3199.4375 677.8523)))
(apply 'command (append '("pline") coords '("c")))
(setq currobj (ssadd (entlast) currobj))
(setq coords (list 
(list 3199.4375 677.7093) 
(list 3125.415 677.6593) 
(list 3125.415 677.4823) 
(list 3199.4375 677.6323)))
(apply 'command (append '("pline") coords '("c")))
(setq currobj (ssadd (entlast) currobj))
(setq coords (list 
(list 3199.4375 677.4893) 
(list 3125.415 677.3393) 
(list 3125.415 677.1623) 
(list 3199.4375 677.4123)))
(apply 'command (append '("pline") coords '("c")))
(setq currobj (ssadd (entlast) currobj))
(setq coords (list 
(list 3199.4375 677.2693) 
(list 3125.415 677.0193) 
(list 3125.415 676.8423) 
(list 3199.4375 677.1923)))
(apply 'command (append '("pline") coords '("c")))
(setq currobj (ssadd (entlast) currobj))
(setq coords (list 
(list 3199.4375 677.0493) 
(list 3125.415 676.6993) 
(list 3125.415 676.5223) 
(list 3199.4375 676.9723)))
(apply 'command (append '("pline") coords '("c")))
(setq currobj (ssadd (entlast) currobj))
(setq coords (list 
(list 3199.4375 676.8293) 
(list 3125.415 676.3793) 
(list 3125.415 676.2023) 
(list 3199.4375 676.7523)))
(apply 'command (append '("pline") coords '("c")))
(setq currobj (ssadd (entlast) currobj))
(setq coords (list 
(list 3199.4375 676.6093) 
(list 3125.415 676.0593) 
(list 3125.415 675.8823) 
(list 3199.4375 676.5323)))
(apply 'command (append '("pline") coords '("c")))
(setq currobj (ssadd (entlast) currobj))
(setq coords (list 
(list 3199.4375 676.3893) 
(list 3125.415 675.7393) 
(list 3125.415 675.5623) 
(list 3199.4375 676.3123)))
(apply 'command (append '("pline") coords '("c")))
(setq currobj (ssadd (entlast) currobj))
(command "_layer" "set" "nitride" "")
(command "_layer" "set" "text" "")
(command "_circle" "3199.0625,665.1693" "0.075")
(command "_circle" "3199.0625,665.4693" "0.075")
(command "_circle" "3199.0625,665.7693" "0.075")
(command "_circle" "3199.0625,666.0693" "0.075")
(command "_circle" "3199.0625,666.3693" "0.075")
(command "_circle" "3198.7625,665.1693" "0.075")
(command "_circle" "3198.7625,665.4693" "0.075")
(command "_circle" "3198.7625,665.7693" "0.075")
(command "_circle" "3198.7625,666.0693" "0.075")
(command "_circle" "3198.7625,666.3693" "0.075")
(command "_circle" "3198.4625,665.1693" "0.075")
(command "_circle" "3198.4625,665.4693" "0.075")
(command "_circle" "3198.4625,665.7693" "0.075")
(command "_circle" "3198.4625,666.0693" "0.075")
(command "_circle" "3198.4625,666.3693" "0.075")
(command "_circle" "3198.1625,665.1693" "0.075")
(command "_circle" "3198.1625,665.4693" "0.075")
(command "_circle" "3198.1625,665.7693" "0.075")
(command "_circle" "3198.1625,666.0693" "0.075")
(command "_circle" "3198.1625,666.3693" "0.075")
(command "_circle" "3197.8625,665.1693" "0.075")
(command "_circle" "3197.8625,665.4693" "0.075")
(command "_circle" "3197.8625,665.7693" "0.075")
(command "_circle" "3197.8625,666.0693" "0.075")
(command "_circle" "3197.8625,666.3693" "0.075")
(command "_layer" "set" "nitride" "")
(setq coords (list 
(list 3200.2625 690.6123) 
(list 3200.2625 806.257) 
(list 3199.7375 806.257) 
(list 3199.7375 690.6123)))
(apply 'command (append '("pline") coords '("c")))
(setq currobj (ssadd (entlast) currobj))
(command "_layer" "set" "prebias" "")
(command "_rectangle" "3199.7375,690.6123" "3200.2625,806.257")
(setq currobj (ssadd (entlast) currobj))
(command "_layer" "set" "nitride" "")
(setq coords (list 
(list 3200.2625 806.257) 
(list 3200.5625 816.257) 
(list 3200.5625 816.257) 
(list 3200.5625 817.257) 
(list 3274.585 816.507) 
(list 3274.585 821.45) 
(list 3200.5625 820.7) 
(list 3200.5625 821.7) 
(list 3200.5625 821.7) 
(list 3200.2625 831.7) 
(list 3199.7375 831.7) 
(list 3199.4375 821.7) 
(list 3199.4375 821.7) 
(list 3199.4375 820.7) 
(list 3125.415 821.45) 
(list 3125.415 816.507) 
(list 3199.4375 817.257) 
(list 3199.4375 816.257) 
(list 3199.4375 816.257) 
(list 3199.7375 806.257)))
(apply 'command (append '("pline") coords '("c")))
(setq currobj (ssadd (entlast) currobj))
(command "_layer" "set" "prebias" "")
(setq coords (list 
(list 3199.4375 806.257) 
(list 3199.4375 817.257) 
(list 3125.415 816.507) 
(list 3125.415 821.45) 
(list 3199.4375 820.7) 
(list 3199.4375 831.7) 
(list 3200.5625 831.7) 
(list 3200.5625 820.7) 
(list 3274.585 821.45) 
(list 3274.585 816.507) 
(list 3200.5625 817.257) 
(list 3200.5625 806.257)))
(apply 'command (append '("pline") coords '("c")))
(setq currobj (ssadd (entlast) currobj))
(command "_layer" "set" "nitride" "")
(command "_layer" "set" "fda1" "")
(setq coords (list 
(list 3200.5625 817.4) 
(list 3274.585 816.65) 
(list 3274.585 816.827) 
(list 3200.5625 817.477)))
(apply 'command (append '("pline") coords '("c")))
(setq currobj (ssadd (entlast) currobj))
(setq coords (list 
(list 3200.5625 817.62) 
(list 3274.585 816.97) 
(list 3274.585 817.147) 
(list 3200.5625 817.697)))
(apply 'command (append '("pline") coords '("c")))
(setq currobj (ssadd (entlast) currobj))
(setq coords (list 
(list 3200.5625 817.84) 
(list 3274.585 817.29) 
(list 3274.585 817.467) 
(list 3200.5625 817.917)))
(apply 'command (append '("pline") coords '("c")))
(setq currobj (ssadd (entlast) currobj))
(setq coords (list 
(list 3200.5625 818.06) 
(list 3274.585 817.61) 
(list 3274.585 817.787) 
(list 3200.5625 818.137)))
(apply 'command (append '("pline") coords '("c")))
(setq currobj (ssadd (entlast) currobj))
(setq coords (list 
(list 3200.5625 818.28) 
(list 3274.585 817.93) 
(list 3274.585 818.107) 
(list 3200.5625 818.357)))
(apply 'command (append '("pline") coords '("c")))
(setq currobj (ssadd (entlast) currobj))
(setq coords (list 
(list 3200.5625 818.5) 
(list 3274.585 818.25) 
(list 3274.585 818.427) 
(list 3200.5625 818.577)))
(apply 'command (append '("pline") coords '("c")))
(setq currobj (ssadd (entlast) currobj))
(setq coords (list 
(list 3200.5625 818.72) 
(list 3274.585 818.57) 
(list 3274.585 818.747) 
(list 3200.5625 818.797)))
(apply 'command (append '("pline") coords '("c")))
(setq currobj (ssadd (entlast) currobj))
(setq coords (list 
(list 3200.5625 818.94) 
(list 3274.585 818.89) 
(list 3274.585 819.067) 
(list 3200.5625 819.017)))
(apply 'command (append '("pline") coords '("c")))
(setq currobj (ssadd (entlast) currobj))
(setq coords (list 
(list 3200.5625 819.16) 
(list 3274.585 819.21) 
(list 3274.585 819.387) 
(list 3200.5625 819.237)))
(apply 'command (append '("pline") coords '("c")))
(setq currobj (ssadd (entlast) currobj))
(setq coords (list 
(list 3200.5625 819.38) 
(list 3274.585 819.53) 
(list 3274.585 819.707) 
(list 3200.5625 819.457)))
(apply 'command (append '("pline") coords '("c")))
(setq currobj (ssadd (entlast) currobj))
(setq coords (list 
(list 3200.5625 819.6) 
(list 3274.585 819.85) 
(list 3274.585 820.027) 
(list 3200.5625 819.677)))
(apply 'command (append '("pline") coords '("c")))
(setq currobj (ssadd (entlast) currobj))
(setq coords (list 
(list 3200.5625 819.82) 
(list 3274.585 820.17) 
(list 3274.585 820.347) 
(list 3200.5625 819.897)))
(apply 'command (append '("pline") coords '("c")))
(setq currobj (ssadd (entlast) currobj))
(setq coords (list 
(list 3200.5625 820.04) 
(list 3274.585 820.49) 
(list 3274.585 820.667) 
(list 3200.5625 820.117)))
(apply 'command (append '("pline") coords '("c")))
(setq currobj (ssadd (entlast) currobj))
(setq coords (list 
(list 3200.5625 820.26) 
(list 3274.585 820.81) 
(list 3274.585 820.987) 
(list 3200.5625 820.337)))
(apply 'command (append '("pline") coords '("c")))
(setq currobj (ssadd (entlast) currobj))
(setq coords (list 
(list 3200.5625 820.48) 
(list 3274.585 821.13) 
(list 3274.585 821.307) 
(list 3200.5625 820.557)))
(apply 'command (append '("pline") coords '("c")))
(setq currobj (ssadd (entlast) currobj))
(setq coords (list 
(list 3199.4375 820.557) 
(list 3125.415 821.307) 
(list 3125.415 821.13) 
(list 3199.4375 820.48)))
(apply 'command (append '("pline") coords '("c")))
(setq currobj (ssadd (entlast) currobj))
(setq coords (list 
(list 3199.4375 820.337) 
(list 3125.415 820.987) 
(list 3125.415 820.81) 
(list 3199.4375 820.26)))
(apply 'command (append '("pline") coords '("c")))
(setq currobj (ssadd (entlast) currobj))
(setq coords (list 
(list 3199.4375 820.117) 
(list 3125.415 820.667) 
(list 3125.415 820.49) 
(list 3199.4375 820.04)))
(apply 'command (append '("pline") coords '("c")))
(setq currobj (ssadd (entlast) currobj))
(setq coords (list 
(list 3199.4375 819.897) 
(list 3125.415 820.347) 
(list 3125.415 820.17) 
(list 3199.4375 819.82)))
(apply 'command (append '("pline") coords '("c")))
(setq currobj (ssadd (entlast) currobj))
(setq coords (list 
(list 3199.4375 819.677) 
(list 3125.415 820.027) 
(list 3125.415 819.85) 
(list 3199.4375 819.6)))
(apply 'command (append '("pline") coords '("c")))
(setq currobj (ssadd (entlast) currobj))
(setq coords (list 
(list 3199.4375 819.457) 
(list 3125.415 819.707) 
(list 3125.415 819.53) 
(list 3199.4375 819.38)))
(apply 'command (append '("pline") coords '("c")))
(setq currobj (ssadd (entlast) currobj))
(setq coords (list 
(list 3199.4375 819.237) 
(list 3125.415 819.387) 
(list 3125.415 819.21) 
(list 3199.4375 819.16)))
(apply 'command (append '("pline") coords '("c")))
(setq currobj (ssadd (entlast) currobj))
(setq coords (list 
(list 3199.4375 819.017) 
(list 3125.415 819.067) 
(list 3125.415 818.89) 
(list 3199.4375 818.94)))
(apply 'command (append '("pline") coords '("c")))
(setq currobj (ssadd (entlast) currobj))
(setq coords (list 
(list 3199.4375 818.797) 
(list 3125.415 818.747) 
(list 3125.415 818.57) 
(list 3199.4375 818.72)))
(apply 'command (append '("pline") coords '("c")))
(setq currobj (ssadd (entlast) currobj))
(setq coords (list 
(list 3199.4375 818.577) 
(list 3125.415 818.427) 
(list 3125.415 818.25) 
(list 3199.4375 818.5)))
(apply 'command (append '("pline") coords '("c")))
(setq currobj (ssadd (entlast) currobj))
(setq coords (list 
(list 3199.4375 818.357) 
(list 3125.415 818.107) 
(list 3125.415 817.93) 
(list 3199.4375 818.28)))
(apply 'command (append '("pline") coords '("c")))
(setq currobj (ssadd (entlast) currobj))
(setq coords (list 
(list 3199.4375 818.137) 
(list 3125.415 817.787) 
(list 3125.415 817.61) 
(list 3199.4375 818.06)))
(apply 'command (append '("pline") coords '("c")))
(setq currobj (ssadd (entlast) currobj))
(setq coords (list 
(list 3199.4375 817.917) 
(list 3125.415 817.467) 
(list 3125.415 817.29) 
(list 3199.4375 817.84)))
(apply 'command (append '("pline") coords '("c")))
(setq currobj (ssadd (entlast) currobj))
(setq coords (list 
(list 3199.4375 817.697) 
(list 3125.415 817.147) 
(list 3125.415 816.97) 
(list 3199.4375 817.62)))
(apply 'command (append '("pline") coords '("c")))
(setq currobj (ssadd (entlast) currobj))
(setq coords (list 
(list 3199.4375 817.477) 
(list 3125.415 816.827) 
(list 3125.415 816.65) 
(list 3199.4375 817.4)))
(apply 'command (append '("pline") coords '("c")))
(setq currobj (ssadd (entlast) currobj))
(command "_layer" "set" "nitride" "")
(command "_layer" "set" "text" "")
(command "_circle" "3199.0625,806.257" "0.075")
(command "_circle" "3199.0625,806.557" "0.075")
(command "_circle" "3199.0625,806.857" "0.075")
(command "_circle" "3199.0625,807.157" "0.075")
(command "_circle" "3199.0625,807.457" "0.075")
(command "_circle" "3198.7625,806.257" "0.075")
(command "_circle" "3198.7625,806.557" "0.075")
(command "_circle" "3198.7625,806.857" "0.075")
(command "_circle" "3198.7625,807.157" "0.075")
(command "_circle" "3198.7625,807.457" "0.075")
(command "_circle" "3198.4625,806.257" "0.075")
(command "_circle" "3198.4625,806.557" "0.075")
(command "_circle" "3198.4625,806.857" "0.075")
(command "_circle" "3198.4625,807.157" "0.075")
(command "_circle" "3198.4625,807.457" "0.075")
(command "_circle" "3198.1625,806.257" "0.075")
(command "_circle" "3198.1625,806.557" "0.075")
(command "_circle" "3198.1625,806.857" "0.075")
(command "_circle" "3198.1625,807.157" "0.075")
(command "_circle" "3198.1625,807.457" "0.075")
(command "_circle" "3197.8625,806.257" "0.075")
(command "_circle" "3197.8625,806.557" "0.075")
(command "_circle" "3197.8625,806.857" "0.075")
(command "_circle" "3197.8625,807.157" "0.075")
(command "_circle" "3197.8625,807.457" "0.075")
(command "_layer" "set" "nitride" "")
(setq coords (list 
(list 3200.2625 831.7) 
(list 3200.2625 836.7) 
(list 3199.7375 836.7) 
(list 3199.7375 831.7)))
(apply 'command (append '("pline") coords '("c")))
(setq currobj (ssadd (entlast) currobj))
(command "_layer" "set" "prebias" "")
(command "_rectangle" "3199.7375,831.7" "3200.2625,836.7")
(setq currobj (ssadd (entlast) currobj))
(command "_layer" "set" "nitride" "")
(setq cooledsinglenanobeam10 currobj)
(setq currobj nil)
(setq currobj (ssadd))
; DRAWING PHOTONIC CRYSTAL
(command "_layer" "set" "negYjunc" "")
(setq coords (list 
(list 3200.135 866.7) 
(list 3200 851.7) 
(list 3200 866.7)))
(apply 'command (append '("pline") coords '("c")))
(setq currobj (ssadd (entlast) currobj))
(setq coords (list 
(list 3200.2625 836.7) 
(list 3200.415 866.7) 
(list 3201.131 866.7) 
(list 3201.131 836.7)))
(apply 'command (append '("pline") coords '("c")))
(setq currobj (ssadd (entlast) currobj))
(setq coords (list 
(list 3199.865 866.7) 
(list 3200 851.7) 
(list 3200 866.7)))
(apply 'command (append '("pline") coords '("c")))
(setq currobj (ssadd (entlast) currobj))
(setq coords (list 
(list 3199.7375 836.7) 
(list 3199.585 866.7) 
(list 3198.869 866.7) 
(list 3198.869 836.7)))
(apply 'command (append '("pline") coords '("c")))
(setq currobj (ssadd (entlast) currobj))
(command "_layer" "set" "nitride" "")
(setq yjunction10 currobj)
(setq currobj nil)
(setq currobj (ssadd))
(setq tap10 nil)
(setq tap10 (ssadd))
(command "_layer" "set" "phc" "")
(setq coords (list 
(list 3200 866.7) 
(list 3200.135 866.7) 
(list 3200.135 866.7103) 
(list 3200.135 866.7206) 
(list 3200.135 866.7308) 
(list 3200.135 866.7411) 
(list 3200.135 866.7514) 
(list 3200.135 866.7617) 
(list 3200.135 866.7719) 
(list 3200.135 866.7822) 
(list 3200.135 866.7925) 
(list 3200.135 866.8028) 
(list 3200.135 866.8131) 
(list 3200.135 866.8233) 
(list 3200.135 866.8336) 
(list 3200.135 866.8439) 
(list 3200.135 866.8542) 
(list 3200.135 866.8644) 
(list 3200.135 866.8747) 
(list 3200.135 866.885) 
(list 3200.135 866.8953) 
(list 3200.135 866.9056) 
(list 3200.135 866.9158) 
(list 3200.135 866.9261) 
(list 3200.135 866.9364) 
(list 3200.135 866.9467) 
(list 3200.135 866.9569) 
(list 3200.135 866.9672) 
(list 3200.135 866.9775) 
(list 3200.135 866.9878) 
(list 3200.135 866.9981) 
(list 3200.135 867.0083) 
(list 3200.135 867.0186) 
(list 3200.135 867.0289) 
(list 3200.135 867.0392) 
(list 3200.135 867.0494) 
(list 3200.135 867.0597) 
(list 3200.135 867.07) 
(list 3200 867.07)))
(apply 'command (append '("pline") coords '("c")))
(setq tap10 (ssadd (entlast) tap10))
(command "_mirror" (entlast) "" "3200,900" "3200,901" "No")
(setq tap10 (ssadd (entlast) tap10))
(setq coords (list 
(list 3200.425 866.7) 
(list 3200.415 866.7) 
(list 3200.4153 866.7103) 
(list 3200.4155 866.7206) 
(list 3200.4157 866.7308) 
(list 3200.4159 866.7411) 
(list 3200.4159 866.7514) 
(list 3200.4159 866.7617) 
(list 3200.4158 866.7719) 
(list 3200.4156 866.7822) 
(list 3200.4153 866.7925) 
(list 3200.4149 866.8028) 
(list 3200.4144 866.8131) 
(list 3200.4139 866.8233) 
(list 3200.4133 866.8336) 
(list 3200.4127 866.8439) 
(list 3200.4122 866.8542) 
(list 3200.4117 866.8644) 
(list 3200.4113 866.8747) 
(list 3200.4111 866.885) 
(list 3200.4109 866.8953) 
(list 3200.4109 866.9056) 
(list 3200.4111 866.9158) 
(list 3200.4115 866.9261) 
(list 3200.412 866.9364) 
(list 3200.4127 866.9467) 
(list 3200.4136 866.9569) 
(list 3200.4146 866.9672) 
(list 3200.4158 866.9775) 
(list 3200.417 866.9878) 
(list 3200.4183 866.9981) 
(list 3200.4196 867.0083) 
(list 3200.4209 867.0186) 
(list 3200.4221 867.0289) 
(list 3200.4231 867.0392) 
(list 3200.424 867.0494) 
(list 3200.4246 867.0597) 
(list 3200.425 867.07) 
(list 3200.425 867.07)))
(apply 'command (append '("pline") coords '("c")))
(setq tap10 (ssadd (entlast) tap10))
(command "_mirror" (entlast) "" "3200,900" "3200,901" "No")
(setq tap10 (ssadd (entlast) tap10))
(setq coords (list 
(list 3201.131 866.7) 
(list 3200.425 866.7) 
(list 3200.425 866.7103) 
(list 3200.425 866.7206) 
(list 3200.425 866.7308) 
(list 3200.425 866.7411) 
(list 3200.425 866.7514) 
(list 3200.425 866.7617) 
(list 3200.425 866.7719) 
(list 3200.425 866.7822) 
(list 3200.425 866.7925) 
(list 3200.425 866.8028) 
(list 3200.425 866.8131) 
(list 3200.425 866.8233) 
(list 3200.425 866.8336) 
(list 3200.425 866.8439) 
(list 3200.425 866.8542) 
(list 3200.425 866.8644) 
(list 3200.425 866.8747) 
(list 3200.425 866.885) 
(list 3200.425 866.8953) 
(list 3200.425 866.9056) 
(list 3200.425 866.9158) 
(list 3200.425 866.9261) 
(list 3200.425 866.9364) 
(list 3200.425 866.9467) 
(list 3200.425 866.9569) 
(list 3200.425 866.9672) 
(list 3200.425 866.9775) 
(list 3200.425 866.9878) 
(list 3200.425 866.9981) 
(list 3200.425 867.0083) 
(list 3200.425 867.0186) 
(list 3200.425 867.0289) 
(list 3200.425 867.0392) 
(list 3200.425 867.0494) 
(list 3200.425 867.0597) 
(list 3200.425 867.07) 
(list 3201.131 867.07)))
(apply 'command (append '("pline") coords '("c")))
(setq tap10 (ssadd (entlast) tap10))
(command "_mirror" (entlast) "" "3200,900" "3200,901" "No")
(setq tap10 (ssadd (entlast) tap10))
(setq coords (list 
(list 3200 867.07) 
(list 3200.135 867.07) 
(list 3200.135 867.0803) 
(list 3200.135 867.0906) 
(list 3200.135 867.1008) 
(list 3200.135 867.1111) 
(list 3200.135 867.1214) 
(list 3200.135 867.1317) 
(list 3200.135 867.1419) 
(list 3200.135 867.1522) 
(list 3200.135 867.1625) 
(list 3200.135 867.1728) 
(list 3200.135 867.1831) 
(list 3200.135 867.1933) 
(list 3200.135 867.2036) 
(list 3200.135 867.2139) 
(list 3200.135 867.2242) 
(list 3200.135 867.2344) 
(list 3200.135 867.2447) 
(list 3200.135 867.255) 
(list 3200.135 867.2653) 
(list 3200.135 867.2756) 
(list 3200.135 867.2858) 
(list 3200.135 867.2961) 
(list 3200.135 867.3064) 
(list 3200.135 867.3167) 
(list 3200.135 867.3269) 
(list 3200.135 867.3372) 
(list 3200.135 867.3475) 
(list 3200.135 867.3578) 
(list 3200.135 867.3681) 
(list 3200.135 867.3783) 
(list 3200.135 867.3886) 
(list 3200.135 867.3989) 
(list 3200.135 867.4092) 
(list 3200.135 867.4194) 
(list 3200.135 867.4297) 
(list 3200.135 867.44) 
(list 3200 867.44)))
(apply 'command (append '("pline") coords '("c")))
(setq tap10 (ssadd (entlast) tap10))
(command "_mirror" (entlast) "" "3200,900" "3200,901" "No")
(setq tap10 (ssadd (entlast) tap10))
(setq coords (list 
(list 3200.4351 867.07) 
(list 3200.425 867.07) 
(list 3200.4252 867.0803) 
(list 3200.425 867.0906) 
(list 3200.4246 867.1008) 
(list 3200.4238 867.1111) 
(list 3200.4228 867.1214) 
(list 3200.4215 867.1317) 
(list 3200.4199 867.1419) 
(list 3200.4182 867.1522) 
(list 3200.4163 867.1625) 
(list 3200.4144 867.1728) 
(list 3200.4124 867.1831) 
(list 3200.4104 867.1933) 
(list 3200.4086 867.2036) 
(list 3200.4069 867.2139) 
(list 3200.4055 867.2242) 
(list 3200.4044 867.2344) 
(list 3200.4036 867.2447) 
(list 3200.4032 867.255) 
(list 3200.4031 867.2653) 
(list 3200.4036 867.2756) 
(list 3200.4044 867.2858) 
(list 3200.4057 867.2961) 
(list 3200.4073 867.3064) 
(list 3200.4093 867.3167) 
(list 3200.4116 867.3269) 
(list 3200.4142 867.3372) 
(list 3200.4169 867.3475) 
(list 3200.4197 867.3578) 
(list 3200.4225 867.3681) 
(list 3200.4252 867.3783) 
(list 3200.4277 867.3886) 
(list 3200.43 867.3989) 
(list 3200.4319 867.4092) 
(list 3200.4335 867.4194) 
(list 3200.4345 867.4297) 
(list 3200.4351 867.44) 
(list 3200.4351 867.44)))
(apply 'command (append '("pline") coords '("c")))
(setq tap10 (ssadd (entlast) tap10))
(command "_mirror" (entlast) "" "3200,900" "3200,901" "No")
(setq tap10 (ssadd (entlast) tap10))
(setq coords (list 
(list 3201.131 867.07) 
(list 3200.4351 867.07) 
(list 3200.4351 867.0803) 
(list 3200.4351 867.0906) 
(list 3200.4351 867.1008) 
(list 3200.4351 867.1111) 
(list 3200.4351 867.1214) 
(list 3200.4351 867.1317) 
(list 3200.4351 867.1419) 
(list 3200.4351 867.1522) 
(list 3200.4351 867.1625) 
(list 3200.4351 867.1728) 
(list 3200.4351 867.1831) 
(list 3200.4351 867.1933) 
(list 3200.4351 867.2036) 
(list 3200.4351 867.2139) 
(list 3200.4351 867.2242) 
(list 3200.4351 867.2344) 
(list 3200.4351 867.2447) 
(list 3200.4351 867.255) 
(list 3200.4351 867.2653) 
(list 3200.4351 867.2756) 
(list 3200.4351 867.2858) 
(list 3200.4351 867.2961) 
(list 3200.4351 867.3064) 
(list 3200.4351 867.3167) 
(list 3200.4351 867.3269) 
(list 3200.4351 867.3372) 
(list 3200.4351 867.3475) 
(list 3200.4351 867.3578) 
(list 3200.4351 867.3681) 
(list 3200.4351 867.3783) 
(list 3200.4351 867.3886) 
(list 3200.4351 867.3989) 
(list 3200.4351 867.4092) 
(list 3200.4351 867.4194) 
(list 3200.4351 867.4297) 
(list 3200.4351 867.44) 
(list 3201.131 867.44)))
(apply 'command (append '("pline") coords '("c")))
(setq tap10 (ssadd (entlast) tap10))
(command "_mirror" (entlast) "" "3200,900" "3200,901" "No")
(setq tap10 (ssadd (entlast) tap10))
(setq coords (list 
(list 3200 867.44) 
(list 3200.135 867.44) 
(list 3200.135 867.4503) 
(list 3200.135 867.4606) 
(list 3200.135 867.4708) 
(list 3200.135 867.4811) 
(list 3200.135 867.4914) 
(list 3200.135 867.5017) 
(list 3200.135 867.5119) 
(list 3200.135 867.5222) 
(list 3200.135 867.5325) 
(list 3200.135 867.5428) 
(list 3200.135 867.5531) 
(list 3200.135 867.5633) 
(list 3200.135 867.5736) 
(list 3200.135 867.5839) 
(list 3200.135 867.5942) 
(list 3200.135 867.6044) 
(list 3200.135 867.6147) 
(list 3200.135 867.625) 
(list 3200.135 867.6353) 
(list 3200.135 867.6456) 
(list 3200.135 867.6558) 
(list 3200.135 867.6661) 
(list 3200.135 867.6764) 
(list 3200.135 867.6867) 
(list 3200.135 867.6969) 
(list 3200.135 867.7072) 
(list 3200.135 867.7175) 
(list 3200.135 867.7278) 
(list 3200.135 867.7381) 
(list 3200.135 867.7483) 
(list 3200.135 867.7586) 
(list 3200.135 867.7689) 
(list 3200.135 867.7792) 
(list 3200.135 867.7894) 
(list 3200.135 867.7997) 
(list 3200.135 867.81) 
(list 3200 867.81)))
(apply 'command (append '("pline") coords '("c")))
(setq tap10 (ssadd (entlast) tap10))
(command "_mirror" (entlast) "" "3200,900" "3200,901" "No")
(setq tap10 (ssadd (entlast) tap10))
(setq coords (list 
(list 3200.4451 867.44) 
(list 3200.4351 867.44) 
(list 3200.4351 867.4503) 
(list 3200.4345 867.4606) 
(list 3200.4334 867.4708) 
(list 3200.4318 867.4811) 
(list 3200.4296 867.4914) 
(list 3200.427 867.5017) 
(list 3200.4241 867.5119) 
(list 3200.4208 867.5222) 
(list 3200.4174 867.5325) 
(list 3200.4139 867.5428) 
(list 3200.4104 867.5531) 
(list 3200.407 867.5633) 
(list 3200.4039 867.5736) 
(list 3200.4011 867.5839) 
(list 3200.3988 867.5942) 
(list 3200.397 867.6044) 
(list 3200.3958 867.6147) 
(list 3200.3953 867.625) 
(list 3200.3954 867.6353) 
(list 3200.3962 867.6456) 
(list 3200.3977 867.6558) 
(list 3200.3998 867.6661) 
(list 3200.4026 867.6764) 
(list 3200.4059 867.6867) 
(list 3200.4096 867.6969) 
(list 3200.4137 867.7072) 
(list 3200.4179 867.7175) 
(list 3200.4223 867.7278) 
(list 3200.4266 867.7381) 
(list 3200.4307 867.7483) 
(list 3200.4345 867.7586) 
(list 3200.4379 867.7689) 
(list 3200.4408 867.7792) 
(list 3200.443 867.7894) 
(list 3200.4444 867.7997) 
(list 3200.4451 867.81) 
(list 3200.4451 867.81)))
(apply 'command (append '("pline") coords '("c")))
(setq tap10 (ssadd (entlast) tap10))
(command "_mirror" (entlast) "" "3200,900" "3200,901" "No")
(setq tap10 (ssadd (entlast) tap10))
(setq coords (list 
(list 3201.131 867.44) 
(list 3200.4451 867.44) 
(list 3200.4451 867.4503) 
(list 3200.4451 867.4606) 
(list 3200.4451 867.4708) 
(list 3200.4451 867.4811) 
(list 3200.4451 867.4914) 
(list 3200.4451 867.5017) 
(list 3200.4451 867.5119) 
(list 3200.4451 867.5222) 
(list 3200.4451 867.5325) 
(list 3200.4451 867.5428) 
(list 3200.4451 867.5531) 
(list 3200.4451 867.5633) 
(list 3200.4451 867.5736) 
(list 3200.4451 867.5839) 
(list 3200.4451 867.5942) 
(list 3200.4451 867.6044) 
(list 3200.4451 867.6147) 
(list 3200.4451 867.625) 
(list 3200.4451 867.6353) 
(list 3200.4451 867.6456) 
(list 3200.4451 867.6558) 
(list 3200.4451 867.6661) 
(list 3200.4451 867.6764) 
(list 3200.4451 867.6867) 
(list 3200.4451 867.6969) 
(list 3200.4451 867.7072) 
(list 3200.4451 867.7175) 
(list 3200.4451 867.7278) 
(list 3200.4451 867.7381) 
(list 3200.4451 867.7483) 
(list 3200.4451 867.7586) 
(list 3200.4451 867.7689) 
(list 3200.4451 867.7792) 
(list 3200.4451 867.7894) 
(list 3200.4451 867.7997) 
(list 3200.4451 867.81) 
(list 3201.131 867.81)))
(apply 'command (append '("pline") coords '("c")))
(setq tap10 (ssadd (entlast) tap10))
(command "_mirror" (entlast) "" "3200,900" "3200,901" "No")
(setq tap10 (ssadd (entlast) tap10))
(setq coords (list 
(list 3200 867.81) 
(list 3200.135 867.81) 
(list 3200.135 867.8203) 
(list 3200.135 867.8306) 
(list 3200.135 867.8408) 
(list 3200.135 867.8511) 
(list 3200.135 867.8614) 
(list 3200.135 867.8717) 
(list 3200.135 867.8819) 
(list 3200.135 867.8922) 
(list 3200.135 867.9025) 
(list 3200.135 867.9128) 
(list 3200.135 867.9231) 
(list 3200.135 867.9333) 
(list 3200.135 867.9436) 
(list 3200.135 867.9539) 
(list 3200.135 867.9642) 
(list 3200.135 867.9744) 
(list 3200.135 867.9847) 
(list 3200.135 867.995) 
(list 3200.135 868.0053) 
(list 3200.135 868.0156) 
(list 3200.135 868.0258) 
(list 3200.135 868.0361) 
(list 3200.135 868.0464) 
(list 3200.135 868.0567) 
(list 3200.135 868.0669) 
(list 3200.135 868.0772) 
(list 3200.135 868.0875) 
(list 3200.135 868.0978) 
(list 3200.135 868.1081) 
(list 3200.135 868.1183) 
(list 3200.135 868.1286) 
(list 3200.135 868.1389) 
(list 3200.135 868.1492) 
(list 3200.135 868.1594) 
(list 3200.135 868.1697) 
(list 3200.135 868.18) 
(list 3200 868.18)))
(apply 'command (append '("pline") coords '("c")))
(setq tap10 (ssadd (entlast) tap10))
(command "_mirror" (entlast) "" "3200,900" "3200,901" "No")
(setq tap10 (ssadd (entlast) tap10))
(setq coords (list 
(list 3200.4551 867.81) 
(list 3200.4451 867.81) 
(list 3200.445 867.8203) 
(list 3200.444 867.8306) 
(list 3200.4422 867.8408) 
(list 3200.4397 867.8511) 
(list 3200.4364 867.8614) 
(list 3200.4326 867.8717) 
(list 3200.4282 867.8819) 
(list 3200.4235 867.8922) 
(list 3200.4185 867.9025) 
(list 3200.4134 867.9128) 
(list 3200.4084 867.9231) 
(list 3200.4036 867.9333) 
(list 3200.3992 867.9436) 
(list 3200.3953 867.9539) 
(list 3200.3921 867.9642) 
(list 3200.3897 867.9744) 
(list 3200.388 867.9847) 
(list 3200.3873 867.995) 
(list 3200.3876 868.0053) 
(list 3200.3888 868.0156) 
(list 3200.391 868.0258) 
(list 3200.394 868.0361) 
(list 3200.3979 868.0464) 
(list 3200.4025 868.0567) 
(list 3200.4076 868.0669) 
(list 3200.4132 868.0772) 
(list 3200.419 868.0875) 
(list 3200.4249 868.0978) 
(list 3200.4307 868.1081) 
(list 3200.4363 868.1183) 
(list 3200.4414 868.1286) 
(list 3200.4459 868.1389) 
(list 3200.4496 868.1492) 
(list 3200.4524 868.1594) 
(list 3200.4543 868.1697) 
(list 3200.4551 868.18) 
(list 3200.4551 868.18)))
(apply 'command (append '("pline") coords '("c")))
(setq tap10 (ssadd (entlast) tap10))
(command "_mirror" (entlast) "" "3200,900" "3200,901" "No")
(setq tap10 (ssadd (entlast) tap10))
(setq coords (list 
(list 3201.131 867.81) 
(list 3200.4551 867.81) 
(list 3200.4551 867.8203) 
(list 3200.4551 867.8306) 
(list 3200.4551 867.8408) 
(list 3200.4551 867.8511) 
(list 3200.4551 867.8614) 
(list 3200.4551 867.8717) 
(list 3200.4551 867.8819) 
(list 3200.4551 867.8922) 
(list 3200.4551 867.9025) 
(list 3200.4551 867.9128) 
(list 3200.4551 867.9231) 
(list 3200.4551 867.9333) 
(list 3200.4551 867.9436) 
(list 3200.4551 867.9539) 
(list 3200.4551 867.9642) 
(list 3200.4551 867.9744) 
(list 3200.4551 867.9847) 
(list 3200.4551 867.995) 
(list 3200.4551 868.0053) 
(list 3200.4551 868.0156) 
(list 3200.4551 868.0258) 
(list 3200.4551 868.0361) 
(list 3200.4551 868.0464) 
(list 3200.4551 868.0567) 
(list 3200.4551 868.0669) 
(list 3200.4551 868.0772) 
(list 3200.4551 868.0875) 
(list 3200.4551 868.0978) 
(list 3200.4551 868.1081) 
(list 3200.4551 868.1183) 
(list 3200.4551 868.1286) 
(list 3200.4551 868.1389) 
(list 3200.4551 868.1492) 
(list 3200.4551 868.1594) 
(list 3200.4551 868.1697) 
(list 3200.4551 868.18) 
(list 3201.131 868.18)))
(apply 'command (append '("pline") coords '("c")))
(setq tap10 (ssadd (entlast) tap10))
(command "_mirror" (entlast) "" "3200,900" "3200,901" "No")
(setq tap10 (ssadd (entlast) tap10))
(setq coords (list 
(list 3200 868.18) 
(list 3200.135 868.18) 
(list 3200.135 868.1903) 
(list 3200.135 868.2006) 
(list 3200.135 868.2108) 
(list 3200.135 868.2211) 
(list 3200.135 868.2314) 
(list 3200.135 868.2417) 
(list 3200.135 868.2519) 
(list 3200.135 868.2622) 
(list 3200.135 868.2725) 
(list 3200.135 868.2828) 
(list 3200.135 868.2931) 
(list 3200.135 868.3033) 
(list 3200.135 868.3136) 
(list 3200.135 868.3239) 
(list 3200.135 868.3342) 
(list 3200.135 868.3444) 
(list 3200.135 868.3547) 
(list 3200.135 868.365) 
(list 3200.135 868.3753) 
(list 3200.135 868.3856) 
(list 3200.135 868.3958) 
(list 3200.135 868.4061) 
(list 3200.135 868.4164) 
(list 3200.135 868.4267) 
(list 3200.135 868.4369) 
(list 3200.135 868.4472) 
(list 3200.135 868.4575) 
(list 3200.135 868.4678) 
(list 3200.135 868.4781) 
(list 3200.135 868.4883) 
(list 3200.135 868.4986) 
(list 3200.135 868.5089) 
(list 3200.135 868.5192) 
(list 3200.135 868.5294) 
(list 3200.135 868.5397) 
(list 3200.135 868.55) 
(list 3200 868.55)))
(apply 'command (append '("pline") coords '("c")))
(setq tap10 (ssadd (entlast) tap10))
(command "_mirror" (entlast) "" "3200,900" "3200,901" "No")
(setq tap10 (ssadd (entlast) tap10))
(setq coords (list 
(list 3200.4652 868.18) 
(list 3200.4551 868.18) 
(list 3200.4549 868.1903) 
(list 3200.4535 868.2006) 
(list 3200.4511 868.2108) 
(list 3200.4476 868.2211) 
(list 3200.4433 868.2314) 
(list 3200.4381 868.2417) 
(list 3200.4323 868.2519) 
(list 3200.4261 868.2622) 
(list 3200.4195 868.2725) 
(list 3200.4129 868.2828) 
(list 3200.4064 868.2931) 
(list 3200.4002 868.3033) 
(list 3200.3945 868.3136) 
(list 3200.3895 868.3239) 
(list 3200.3854 868.3342) 
(list 3200.3823 868.3444) 
(list 3200.3803 868.3547) 
(list 3200.3794 868.365) 
(list 3200.3798 868.3753) 
(list 3200.3815 868.3856) 
(list 3200.3843 868.3958) 
(list 3200.3882 868.4061) 
(list 3200.3932 868.4164) 
(list 3200.3991 868.4267) 
(list 3200.4056 868.4369) 
(list 3200.4127 868.4472) 
(list 3200.4201 868.4575) 
(list 3200.4275 868.4678) 
(list 3200.4349 868.4781) 
(list 3200.4418 868.4883) 
(list 3200.4482 868.4986) 
(list 3200.4538 868.5089) 
(list 3200.4584 868.5192) 
(list 3200.4619 868.5294) 
(list 3200.4642 868.5397) 
(list 3200.4652 868.55) 
(list 3200.4652 868.55)))
(apply 'command (append '("pline") coords '("c")))
(setq tap10 (ssadd (entlast) tap10))
(command "_mirror" (entlast) "" "3200,900" "3200,901" "No")
(setq tap10 (ssadd (entlast) tap10))
(setq coords (list 
(list 3201.131 868.18) 
(list 3200.4652 868.18) 
(list 3200.4652 868.1903) 
(list 3200.4652 868.2006) 
(list 3200.4652 868.2108) 
(list 3200.4652 868.2211) 
(list 3200.4652 868.2314) 
(list 3200.4652 868.2417) 
(list 3200.4652 868.2519) 
(list 3200.4652 868.2622) 
(list 3200.4652 868.2725) 
(list 3200.4652 868.2828) 
(list 3200.4652 868.2931) 
(list 3200.4652 868.3033) 
(list 3200.4652 868.3136) 
(list 3200.4652 868.3239) 
(list 3200.4652 868.3342) 
(list 3200.4652 868.3444) 
(list 3200.4652 868.3547) 
(list 3200.4652 868.365) 
(list 3200.4652 868.3753) 
(list 3200.4652 868.3856) 
(list 3200.4652 868.3958) 
(list 3200.4652 868.4061) 
(list 3200.4652 868.4164) 
(list 3200.4652 868.4267) 
(list 3200.4652 868.4369) 
(list 3200.4652 868.4472) 
(list 3200.4652 868.4575) 
(list 3200.4652 868.4678) 
(list 3200.4652 868.4781) 
(list 3200.4652 868.4883) 
(list 3200.4652 868.4986) 
(list 3200.4652 868.5089) 
(list 3200.4652 868.5192) 
(list 3200.4652 868.5294) 
(list 3200.4652 868.5397) 
(list 3200.4652 868.55) 
(list 3201.131 868.55)))
(apply 'command (append '("pline") coords '("c")))
(setq tap10 (ssadd (entlast) tap10))
(command "_mirror" (entlast) "" "3200,900" "3200,901" "No")
(setq tap10 (ssadd (entlast) tap10))
(setq coords (list 
(list 3200 868.55) 
(list 3200.135 868.55) 
(list 3200.135 868.5603) 
(list 3200.135 868.5706) 
(list 3200.135 868.5808) 
(list 3200.135 868.5911) 
(list 3200.135 868.6014) 
(list 3200.135 868.6117) 
(list 3200.135 868.6219) 
(list 3200.135 868.6322) 
(list 3200.135 868.6425) 
(list 3200.135 868.6528) 
(list 3200.135 868.6631) 
(list 3200.135 868.6733) 
(list 3200.135 868.6836) 
(list 3200.135 868.6939) 
(list 3200.135 868.7042) 
(list 3200.135 868.7144) 
(list 3200.135 868.7247) 
(list 3200.135 868.735) 
(list 3200.135 868.7453) 
(list 3200.135 868.7556) 
(list 3200.135 868.7658) 
(list 3200.135 868.7761) 
(list 3200.135 868.7864) 
(list 3200.135 868.7967) 
(list 3200.135 868.8069) 
(list 3200.135 868.8172) 
(list 3200.135 868.8275) 
(list 3200.135 868.8378) 
(list 3200.135 868.8481) 
(list 3200.135 868.8583) 
(list 3200.135 868.8686) 
(list 3200.135 868.8789) 
(list 3200.135 868.8892) 
(list 3200.135 868.8994) 
(list 3200.135 868.9097) 
(list 3200.135 868.92) 
(list 3200 868.92)))
(apply 'command (append '("pline") coords '("c")))
(setq tap10 (ssadd (entlast) tap10))
(command "_mirror" (entlast) "" "3200,900" "3200,901" "No")
(setq tap10 (ssadd (entlast) tap10))
(setq coords (list 
(list 3200.4752 868.55) 
(list 3200.4652 868.55) 
(list 3200.4648 868.5603) 
(list 3200.463 868.5706) 
(list 3200.4599 868.5808) 
(list 3200.4556 868.5911) 
(list 3200.4501 868.6014) 
(list 3200.4437 868.6117) 
(list 3200.4365 868.6219) 
(list 3200.4287 868.6322) 
(list 3200.4206 868.6425) 
(list 3200.4124 868.6528) 
(list 3200.4044 868.6631) 
(list 3200.3968 868.6733) 
(list 3200.3898 868.6836) 
(list 3200.3837 868.6939) 
(list 3200.3787 868.7042) 
(list 3200.3749 868.7144) 
(list 3200.3725 868.7247) 
(list 3200.3715 868.735) 
(list 3200.3721 868.7453) 
(list 3200.3741 868.7556) 
(list 3200.3776 868.7658) 
(list 3200.3824 868.7761) 
(list 3200.3885 868.7864) 
(list 3200.3956 868.7967) 
(list 3200.4036 868.8069) 
(list 3200.4122 868.8172) 
(list 3200.4211 868.8275) 
(list 3200.4302 868.8378) 
(list 3200.439 868.8481) 
(list 3200.4474 868.8583) 
(list 3200.455 868.8686) 
(list 3200.4617 868.8789) 
(list 3200.4673 868.8892) 
(list 3200.4714 868.8994) 
(list 3200.4741 868.9097) 
(list 3200.4752 868.92) 
(list 3200.4752 868.92)))
(apply 'command (append '("pline") coords '("c")))
(setq tap10 (ssadd (entlast) tap10))
(command "_mirror" (entlast) "" "3200,900" "3200,901" "No")
(setq tap10 (ssadd (entlast) tap10))
(setq coords (list 
(list 3201.131 868.55) 
(list 3200.4752 868.55) 
(list 3200.4752 868.5603) 
(list 3200.4752 868.5706) 
(list 3200.4752 868.5808) 
(list 3200.4752 868.5911) 
(list 3200.4752 868.6014) 
(list 3200.4752 868.6117) 
(list 3200.4752 868.6219) 
(list 3200.4752 868.6322) 
(list 3200.4752 868.6425) 
(list 3200.4752 868.6528) 
(list 3200.4752 868.6631) 
(list 3200.4752 868.6733) 
(list 3200.4752 868.6836) 
(list 3200.4752 868.6939) 
(list 3200.4752 868.7042) 
(list 3200.4752 868.7144) 
(list 3200.4752 868.7247) 
(list 3200.4752 868.735) 
(list 3200.4752 868.7453) 
(list 3200.4752 868.7556) 
(list 3200.4752 868.7658) 
(list 3200.4752 868.7761) 
(list 3200.4752 868.7864) 
(list 3200.4752 868.7967) 
(list 3200.4752 868.8069) 
(list 3200.4752 868.8172) 
(list 3200.4752 868.8275) 
(list 3200.4752 868.8378) 
(list 3200.4752 868.8481) 
(list 3200.4752 868.8583) 
(list 3200.4752 868.8686) 
(list 3200.4752 868.8789) 
(list 3200.4752 868.8892) 
(list 3200.4752 868.8994) 
(list 3200.4752 868.9097) 
(list 3200.4752 868.92) 
(list 3201.131 868.92)))
(apply 'command (append '("pline") coords '("c")))
(setq tap10 (ssadd (entlast) tap10))
(command "_mirror" (entlast) "" "3200,900" "3200,901" "No")
(setq tap10 (ssadd (entlast) tap10))
(setq coords (list 
(list 3200 868.92) 
(list 3200.135 868.92) 
(list 3200.135 868.9303) 
(list 3200.135 868.9406) 
(list 3200.135 868.9508) 
(list 3200.135 868.9611) 
(list 3200.135 868.9714) 
(list 3200.135 868.9817) 
(list 3200.135 868.9919) 
(list 3200.135 869.0022) 
(list 3200.135 869.0125) 
(list 3200.135 869.0228) 
(list 3200.135 869.0331) 
(list 3200.135 869.0433) 
(list 3200.135 869.0536) 
(list 3200.135 869.0639) 
(list 3200.135 869.0742) 
(list 3200.135 869.0844) 
(list 3200.135 869.0947) 
(list 3200.135 869.105) 
(list 3200.135 869.1153) 
(list 3200.135 869.1256) 
(list 3200.135 869.1358) 
(list 3200.135 869.1461) 
(list 3200.135 869.1564) 
(list 3200.135 869.1667) 
(list 3200.135 869.1769) 
(list 3200.135 869.1872) 
(list 3200.135 869.1975) 
(list 3200.135 869.2078) 
(list 3200.135 869.2181) 
(list 3200.135 869.2283) 
(list 3200.135 869.2386) 
(list 3200.135 869.2489) 
(list 3200.135 869.2592) 
(list 3200.135 869.2694) 
(list 3200.135 869.2797) 
(list 3200.135 869.29) 
(list 3200 869.29)))
(apply 'command (append '("pline") coords '("c")))
(setq tap10 (ssadd (entlast) tap10))
(command "_mirror" (entlast) "" "3200,900" "3200,901" "No")
(setq tap10 (ssadd (entlast) tap10))
(setq coords (list 
(list 3200.4852 868.92) 
(list 3200.4752 868.92) 
(list 3200.4747 868.9303) 
(list 3200.4725 868.9406) 
(list 3200.4687 868.9508) 
(list 3200.4635 868.9611) 
(list 3200.4569 868.9714) 
(list 3200.4492 868.9817) 
(list 3200.4406 868.9919) 
(list 3200.4313 869.0022) 
(list 3200.4217 869.0125) 
(list 3200.4119 869.0228) 
(list 3200.4024 869.0331) 
(list 3200.3934 869.0433) 
(list 3200.3851 869.0536) 
(list 3200.3779 869.0639) 
(list 3200.372 869.0742) 
(list 3200.3676 869.0844) 
(list 3200.3648 869.0947) 
(list 3200.3636 869.105) 
(list 3200.3643 869.1153) 
(list 3200.3668 869.1256) 
(list 3200.3709 869.1358) 
(list 3200.3766 869.1461) 
(list 3200.3838 869.1564) 
(list 3200.3922 869.1667) 
(list 3200.4016 869.1769) 
(list 3200.4117 869.1872) 
(list 3200.4222 869.1975) 
(list 3200.4328 869.2078) 
(list 3200.4431 869.2181) 
(list 3200.4529 869.2283) 
(list 3200.4619 869.2386) 
(list 3200.4697 869.2489) 
(list 3200.4761 869.2592) 
(list 3200.4809 869.2694) 
(list 3200.484 869.2797) 
(list 3200.4852 869.29) 
(list 3200.4852 869.29)))
(apply 'command (append '("pline") coords '("c")))
(setq tap10 (ssadd (entlast) tap10))
(command "_mirror" (entlast) "" "3200,900" "3200,901" "No")
(setq tap10 (ssadd (entlast) tap10))
(setq coords (list 
(list 3201.131 868.92) 
(list 3200.4852 868.92) 
(list 3200.4852 868.9303) 
(list 3200.4852 868.9406) 
(list 3200.4852 868.9508) 
(list 3200.4852 868.9611) 
(list 3200.4852 868.9714) 
(list 3200.4852 868.9817) 
(list 3200.4852 868.9919) 
(list 3200.4852 869.0022) 
(list 3200.4852 869.0125) 
(list 3200.4852 869.0228) 
(list 3200.4852 869.0331) 
(list 3200.4852 869.0433) 
(list 3200.4852 869.0536) 
(list 3200.4852 869.0639) 
(list 3200.4852 869.0742) 
(list 3200.4852 869.0844) 
(list 3200.4852 869.0947) 
(list 3200.4852 869.105) 
(list 3200.4852 869.1153) 
(list 3200.4852 869.1256) 
(list 3200.4852 869.1358) 
(list 3200.4852 869.1461) 
(list 3200.4852 869.1564) 
(list 3200.4852 869.1667) 
(list 3200.4852 869.1769) 
(list 3200.4852 869.1872) 
(list 3200.4852 869.1975) 
(list 3200.4852 869.2078) 
(list 3200.4852 869.2181) 
(list 3200.4852 869.2283) 
(list 3200.4852 869.2386) 
(list 3200.4852 869.2489) 
(list 3200.4852 869.2592) 
(list 3200.4852 869.2694) 
(list 3200.4852 869.2797) 
(list 3200.4852 869.29) 
(list 3201.131 869.29)))
(apply 'command (append '("pline") coords '("c")))
(setq tap10 (ssadd (entlast) tap10))
(command "_mirror" (entlast) "" "3200,900" "3200,901" "No")
(setq tap10 (ssadd (entlast) tap10))
(setq coords (list 
(list 3200 869.29) 
(list 3200.135 869.29) 
(list 3200.135 869.3003) 
(list 3200.135 869.3106) 
(list 3200.135 869.3208) 
(list 3200.135 869.3311) 
(list 3200.135 869.3414) 
(list 3200.135 869.3517) 
(list 3200.135 869.3619) 
(list 3200.135 869.3722) 
(list 3200.135 869.3825) 
(list 3200.135 869.3928) 
(list 3200.135 869.4031) 
(list 3200.135 869.4133) 
(list 3200.135 869.4236) 
(list 3200.135 869.4339) 
(list 3200.135 869.4442) 
(list 3200.135 869.4544) 
(list 3200.135 869.4647) 
(list 3200.135 869.475) 
(list 3200.135 869.4853) 
(list 3200.135 869.4956) 
(list 3200.135 869.5058) 
(list 3200.135 869.5161) 
(list 3200.135 869.5264) 
(list 3200.135 869.5367) 
(list 3200.135 869.5469) 
(list 3200.135 869.5572) 
(list 3200.135 869.5675) 
(list 3200.135 869.5778) 
(list 3200.135 869.5881) 
(list 3200.135 869.5983) 
(list 3200.135 869.6086) 
(list 3200.135 869.6189) 
(list 3200.135 869.6292) 
(list 3200.135 869.6394) 
(list 3200.135 869.6497) 
(list 3200.135 869.66) 
(list 3200 869.66)))
(apply 'command (append '("pline") coords '("c")))
(setq tap10 (ssadd (entlast) tap10))
(command "_mirror" (entlast) "" "3200,900" "3200,901" "No")
(setq tap10 (ssadd (entlast) tap10))
(setq coords (list 
(list 3200.4953 869.29) 
(list 3200.4852 869.29) 
(list 3200.4846 869.3003) 
(list 3200.482 869.3106) 
(list 3200.4776 869.3208) 
(list 3200.4714 869.3311) 
(list 3200.4638 869.3414) 
(list 3200.4548 869.3517) 
(list 3200.4447 869.3619) 
(list 3200.4339 869.3722) 
(list 3200.4227 869.3825) 
(list 3200.4114 869.3928) 
(list 3200.4004 869.4031) 
(list 3200.3899 869.4133) 
(list 3200.3804 869.4236) 
(list 3200.3721 869.4339) 
(list 3200.3653 869.4442) 
(list 3200.3602 869.4544) 
(list 3200.357 869.4647) 
(list 3200.3558 869.475) 
(list 3200.3566 869.4853) 
(list 3200.3594 869.4956) 
(list 3200.3642 869.5058) 
(list 3200.3708 869.5161) 
(list 3200.3791 869.5264) 
(list 3200.3888 869.5367) 
(list 3200.3996 869.5469) 
(list 3200.4112 869.5572) 
(list 3200.4233 869.5675) 
(list 3200.4354 869.5778) 
(list 3200.4473 869.5881) 
(list 3200.4585 869.5983) 
(list 3200.4687 869.6086) 
(list 3200.4776 869.6189) 
(list 3200.4849 869.6292) 
(list 3200.4904 869.6394) 
(list 3200.4939 869.6497) 
(list 3200.4953 869.66) 
(list 3200.4953 869.66)))
(apply 'command (append '("pline") coords '("c")))
(setq tap10 (ssadd (entlast) tap10))
(command "_mirror" (entlast) "" "3200,900" "3200,901" "No")
(setq tap10 (ssadd (entlast) tap10))
(setq coords (list 
(list 3201.131 869.29) 
(list 3200.4953 869.29) 
(list 3200.4953 869.3003) 
(list 3200.4953 869.3106) 
(list 3200.4953 869.3208) 
(list 3200.4953 869.3311) 
(list 3200.4953 869.3414) 
(list 3200.4953 869.3517) 
(list 3200.4953 869.3619) 
(list 3200.4953 869.3722) 
(list 3200.4953 869.3825) 
(list 3200.4953 869.3928) 
(list 3200.4953 869.4031) 
(list 3200.4953 869.4133) 
(list 3200.4953 869.4236) 
(list 3200.4953 869.4339) 
(list 3200.4953 869.4442) 
(list 3200.4953 869.4544) 
(list 3200.4953 869.4647) 
(list 3200.4953 869.475) 
(list 3200.4953 869.4853) 
(list 3200.4953 869.4956) 
(list 3200.4953 869.5058) 
(list 3200.4953 869.5161) 
(list 3200.4953 869.5264) 
(list 3200.4953 869.5367) 
(list 3200.4953 869.5469) 
(list 3200.4953 869.5572) 
(list 3200.4953 869.5675) 
(list 3200.4953 869.5778) 
(list 3200.4953 869.5881) 
(list 3200.4953 869.5983) 
(list 3200.4953 869.6086) 
(list 3200.4953 869.6189) 
(list 3200.4953 869.6292) 
(list 3200.4953 869.6394) 
(list 3200.4953 869.6497) 
(list 3200.4953 869.66) 
(list 3201.131 869.66)))
(apply 'command (append '("pline") coords '("c")))
(setq tap10 (ssadd (entlast) tap10))
(command "_mirror" (entlast) "" "3200,900" "3200,901" "No")
(setq tap10 (ssadd (entlast) tap10))
(setq coords (list 
(list 3200 869.66) 
(list 3200.135 869.66) 
(list 3200.135 869.6703) 
(list 3200.135 869.6806) 
(list 3200.135 869.6908) 
(list 3200.135 869.7011) 
(list 3200.135 869.7114) 
(list 3200.135 869.7217) 
(list 3200.135 869.7319) 
(list 3200.135 869.7422) 
(list 3200.135 869.7525) 
(list 3200.135 869.7628) 
(list 3200.135 869.7731) 
(list 3200.135 869.7833) 
(list 3200.135 869.7936) 
(list 3200.135 869.8039) 
(list 3200.135 869.8142) 
(list 3200.135 869.8244) 
(list 3200.135 869.8347) 
(list 3200.135 869.845) 
(list 3200.135 869.8553) 
(list 3200.135 869.8656) 
(list 3200.135 869.8758) 
(list 3200.135 869.8861) 
(list 3200.135 869.8964) 
(list 3200.135 869.9067) 
(list 3200.135 869.9169) 
(list 3200.135 869.9272) 
(list 3200.135 869.9375) 
(list 3200.135 869.9478) 
(list 3200.135 869.9581) 
(list 3200.135 869.9683) 
(list 3200.135 869.9786) 
(list 3200.135 869.9889) 
(list 3200.135 869.9992) 
(list 3200.135 870.0094) 
(list 3200.135 870.0197) 
(list 3200.135 870.03) 
(list 3200 870.03)))
(apply 'command (append '("pline") coords '("c")))
(setq tap10 (ssadd (entlast) tap10))
(command "_mirror" (entlast) "" "3200,900" "3200,901" "No")
(setq tap10 (ssadd (entlast) tap10))
(setq coords (list 
(list 3200.5053 869.66) 
(list 3200.4953 869.66) 
(list 3200.4945 869.6703) 
(list 3200.4915 869.6806) 
(list 3200.4864 869.6908) 
(list 3200.4794 869.7011) 
(list 3200.4706 869.7114) 
(list 3200.4603 869.7217) 
(list 3200.4489 869.7319) 
(list 3200.4366 869.7422) 
(list 3200.4238 869.7525) 
(list 3200.4109 869.7628) 
(list 3200.3984 869.7731) 
(list 3200.3865 869.7833) 
(list 3200.3757 869.7936) 
(list 3200.3663 869.8039) 
(list 3200.3586 869.8142) 
(list 3200.3529 869.8244) 
(list 3200.3492 869.8347) 
(list 3200.3479 869.845) 
(list 3200.3488 869.8553) 
(list 3200.352 869.8656) 
(list 3200.3575 869.8758) 
(list 3200.365 869.8861) 
(list 3200.3744 869.8964) 
(list 3200.3854 869.9067) 
(list 3200.3976 869.9169) 
(list 3200.4107 869.9272) 
(list 3200.4243 869.9375) 
(list 3200.438 869.9478) 
(list 3200.4514 869.9581) 
(list 3200.464 869.9683) 
(list 3200.4755 869.9786) 
(list 3200.4855 869.9889) 
(list 3200.4938 869.9992) 
(list 3200.4999 870.0094) 
(list 3200.5038 870.0197) 
(list 3200.5053 870.03) 
(list 3200.5053 870.03)))
(apply 'command (append '("pline") coords '("c")))
(setq tap10 (ssadd (entlast) tap10))
(command "_mirror" (entlast) "" "3200,900" "3200,901" "No")
(setq tap10 (ssadd (entlast) tap10))
(setq coords (list 
(list 3201.131 869.66) 
(list 3200.5053 869.66) 
(list 3200.5053 869.6703) 
(list 3200.5053 869.6806) 
(list 3200.5053 869.6908) 
(list 3200.5053 869.7011) 
(list 3200.5053 869.7114) 
(list 3200.5053 869.7217) 
(list 3200.5053 869.7319) 
(list 3200.5053 869.7422) 
(list 3200.5053 869.7525) 
(list 3200.5053 869.7628) 
(list 3200.5053 869.7731) 
(list 3200.5053 869.7833) 
(list 3200.5053 869.7936) 
(list 3200.5053 869.8039) 
(list 3200.5053 869.8142) 
(list 3200.5053 869.8244) 
(list 3200.5053 869.8347) 
(list 3200.5053 869.845) 
(list 3200.5053 869.8553) 
(list 3200.5053 869.8656) 
(list 3200.5053 869.8758) 
(list 3200.5053 869.8861) 
(list 3200.5053 869.8964) 
(list 3200.5053 869.9067) 
(list 3200.5053 869.9169) 
(list 3200.5053 869.9272) 
(list 3200.5053 869.9375) 
(list 3200.5053 869.9478) 
(list 3200.5053 869.9581) 
(list 3200.5053 869.9683) 
(list 3200.5053 869.9786) 
(list 3200.5053 869.9889) 
(list 3200.5053 869.9992) 
(list 3200.5053 870.0094) 
(list 3200.5053 870.0197) 
(list 3200.5053 870.03) 
(list 3201.131 870.03)))
(apply 'command (append '("pline") coords '("c")))
(setq tap10 (ssadd (entlast) tap10))
(command "_mirror" (entlast) "" "3200,900" "3200,901" "No")
(setq tap10 (ssadd (entlast) tap10))
(setq coords (list 
(list 3200 870.03) 
(list 3200.135 870.03) 
(list 3200.135 870.0403) 
(list 3200.135 870.0506) 
(list 3200.135 870.0608) 
(list 3200.135 870.0711) 
(list 3200.135 870.0814) 
(list 3200.135 870.0917) 
(list 3200.135 870.1019) 
(list 3200.135 870.1122) 
(list 3200.135 870.1225) 
(list 3200.135 870.1328) 
(list 3200.135 870.1431) 
(list 3200.135 870.1533) 
(list 3200.135 870.1636) 
(list 3200.135 870.1739) 
(list 3200.135 870.1842) 
(list 3200.135 870.1944) 
(list 3200.135 870.2047) 
(list 3200.135 870.215) 
(list 3200.135 870.2253) 
(list 3200.135 870.2356) 
(list 3200.135 870.2458) 
(list 3200.135 870.2561) 
(list 3200.135 870.2664) 
(list 3200.135 870.2767) 
(list 3200.135 870.2869) 
(list 3200.135 870.2972) 
(list 3200.135 870.3075) 
(list 3200.135 870.3178) 
(list 3200.135 870.3281) 
(list 3200.135 870.3383) 
(list 3200.135 870.3486) 
(list 3200.135 870.3589) 
(list 3200.135 870.3692) 
(list 3200.135 870.3794) 
(list 3200.135 870.3897) 
(list 3200.135 870.4) 
(list 3200 870.4)))
(apply 'command (append '("pline") coords '("c")))
(setq tap10 (ssadd (entlast) tap10))
(command "_mirror" (entlast) "" "3200,900" "3200,901" "No")
(setq tap10 (ssadd (entlast) tap10))
(setq coords (list 
(list 3200.5153 870.03) 
(list 3200.5053 870.03) 
(list 3200.5044 870.0403) 
(list 3200.501 870.0506) 
(list 3200.4952 870.0608) 
(list 3200.4873 870.0711) 
(list 3200.4774 870.0814) 
(list 3200.4659 870.0917) 
(list 3200.453 870.1019) 
(list 3200.4392 870.1122) 
(list 3200.4249 870.1225) 
(list 3200.4105 870.1328) 
(list 3200.3964 870.1431) 
(list 3200.3831 870.1533) 
(list 3200.371 870.1636) 
(list 3200.3605 870.1739) 
(list 3200.3519 870.1842) 
(list 3200.3455 870.1944) 
(list 3200.3415 870.2047) 
(list 3200.34 870.215) 
(list 3200.341 870.2253) 
(list 3200.3447 870.2356) 
(list 3200.3508 870.2458) 
(list 3200.3592 870.2561) 
(list 3200.3697 870.2664) 
(list 3200.382 870.2767) 
(list 3200.3956 870.2869) 
(list 3200.4102 870.2972) 
(list 3200.4254 870.3075) 
(list 3200.4407 870.3178) 
(list 3200.4555 870.3281) 
(list 3200.4696 870.3383) 
(list 3200.4824 870.3486) 
(list 3200.4935 870.3589) 
(list 3200.5026 870.3692) 
(list 3200.5094 870.3794) 
(list 3200.5137 870.3897) 
(list 3200.5153 870.4) 
(list 3200.5153 870.4)))
(apply 'command (append '("pline") coords '("c")))
(setq tap10 (ssadd (entlast) tap10))
(command "_mirror" (entlast) "" "3200,900" "3200,901" "No")
(setq tap10 (ssadd (entlast) tap10))
(setq coords (list 
(list 3201.131 870.03) 
(list 3200.5153 870.03) 
(list 3200.5153 870.0403) 
(list 3200.5153 870.0506) 
(list 3200.5153 870.0608) 
(list 3200.5153 870.0711) 
(list 3200.5153 870.0814) 
(list 3200.5153 870.0917) 
(list 3200.5153 870.1019) 
(list 3200.5153 870.1122) 
(list 3200.5153 870.1225) 
(list 3200.5153 870.1328) 
(list 3200.5153 870.1431) 
(list 3200.5153 870.1533) 
(list 3200.5153 870.1636) 
(list 3200.5153 870.1739) 
(list 3200.5153 870.1842) 
(list 3200.5153 870.1944) 
(list 3200.5153 870.2047) 
(list 3200.5153 870.215) 
(list 3200.5153 870.2253) 
(list 3200.5153 870.2356) 
(list 3200.5153 870.2458) 
(list 3200.5153 870.2561) 
(list 3200.5153 870.2664) 
(list 3200.5153 870.2767) 
(list 3200.5153 870.2869) 
(list 3200.5153 870.2972) 
(list 3200.5153 870.3075) 
(list 3200.5153 870.3178) 
(list 3200.5153 870.3281) 
(list 3200.5153 870.3383) 
(list 3200.5153 870.3486) 
(list 3200.5153 870.3589) 
(list 3200.5153 870.3692) 
(list 3200.5153 870.3794) 
(list 3200.5153 870.3897) 
(list 3200.5153 870.4) 
(list 3201.131 870.4)))
(apply 'command (append '("pline") coords '("c")))
(setq tap10 (ssadd (entlast) tap10))
(command "_mirror" (entlast) "" "3200,900" "3200,901" "No")
(setq tap10 (ssadd (entlast) tap10))
(setq coords (list 
(list 3200 870.4) 
(list 3200.135 870.4) 
(list 3200.135 870.4103) 
(list 3200.135 870.4206) 
(list 3200.135 870.4308) 
(list 3200.135 870.4411) 
(list 3200.135 870.4514) 
(list 3200.135 870.4617) 
(list 3200.135 870.4719) 
(list 3200.135 870.4822) 
(list 3200.135 870.4925) 
(list 3200.135 870.5028) 
(list 3200.135 870.5131) 
(list 3200.135 870.5233) 
(list 3200.135 870.5336) 
(list 3200.135 870.5439) 
(list 3200.135 870.5542) 
(list 3200.135 870.5644) 
(list 3200.135 870.5747) 
(list 3200.135 870.585) 
(list 3200.135 870.5953) 
(list 3200.135 870.6056) 
(list 3200.135 870.6158) 
(list 3200.135 870.6261) 
(list 3200.135 870.6364) 
(list 3200.135 870.6467) 
(list 3200.135 870.6569) 
(list 3200.135 870.6672) 
(list 3200.135 870.6775) 
(list 3200.135 870.6878) 
(list 3200.135 870.6981) 
(list 3200.135 870.7083) 
(list 3200.135 870.7186) 
(list 3200.135 870.7289) 
(list 3200.135 870.7392) 
(list 3200.135 870.7494) 
(list 3200.135 870.7597) 
(list 3200.135 870.77) 
(list 3200 870.77)))
(apply 'command (append '("pline") coords '("c")))
(setq tap10 (ssadd (entlast) tap10))
(command "_mirror" (entlast) "" "3200,900" "3200,901" "No")
(setq tap10 (ssadd (entlast) tap10))
(setq coords (list 
(list 3200.5254 870.4) 
(list 3200.5153 870.4) 
(list 3200.5142 870.4103) 
(list 3200.5105 870.4206) 
(list 3200.5041 870.4308) 
(list 3200.4952 870.4411) 
(list 3200.4843 870.4514) 
(list 3200.4714 870.4617) 
(list 3200.4571 870.4719) 
(list 3200.4418 870.4822) 
(list 3200.4259 870.4925) 
(list 3200.41 870.5028) 
(list 3200.3944 870.5131) 
(list 3200.3797 870.5233) 
(list 3200.3663 870.5336) 
(list 3200.3547 870.5439) 
(list 3200.3452 870.5542) 
(list 3200.3381 870.5644) 
(list 3200.3337 870.5747) 
(list 3200.332 870.585) 
(list 3200.3333 870.5953) 
(list 3200.3373 870.6056) 
(list 3200.3441 870.6158) 
(list 3200.3534 870.6261) 
(list 3200.365 870.6364) 
(list 3200.3786 870.6467) 
(list 3200.3936 870.6569) 
(list 3200.4097 870.6672) 
(list 3200.4265 870.6775) 
(list 3200.4433 870.6878) 
(list 3200.4597 870.6981) 
(list 3200.4751 870.7083) 
(list 3200.4892 870.7186) 
(list 3200.5014 870.7289) 
(list 3200.5114 870.7392) 
(list 3200.5189 870.7494) 
(list 3200.5236 870.7597) 
(list 3200.5254 870.77) 
(list 3200.5254 870.77)))
(apply 'command (append '("pline") coords '("c")))
(setq tap10 (ssadd (entlast) tap10))
(command "_mirror" (entlast) "" "3200,900" "3200,901" "No")
(setq tap10 (ssadd (entlast) tap10))
(setq coords (list 
(list 3201.131 870.4) 
(list 3200.5254 870.4) 
(list 3200.5254 870.4103) 
(list 3200.5254 870.4206) 
(list 3200.5254 870.4308) 
(list 3200.5254 870.4411) 
(list 3200.5254 870.4514) 
(list 3200.5254 870.4617) 
(list 3200.5254 870.4719) 
(list 3200.5254 870.4822) 
(list 3200.5254 870.4925) 
(list 3200.5254 870.5028) 
(list 3200.5254 870.5131) 
(list 3200.5254 870.5233) 
(list 3200.5254 870.5336) 
(list 3200.5254 870.5439) 
(list 3200.5254 870.5542) 
(list 3200.5254 870.5644) 
(list 3200.5254 870.5747) 
(list 3200.5254 870.585) 
(list 3200.5254 870.5953) 
(list 3200.5254 870.6056) 
(list 3200.5254 870.6158) 
(list 3200.5254 870.6261) 
(list 3200.5254 870.6364) 
(list 3200.5254 870.6467) 
(list 3200.5254 870.6569) 
(list 3200.5254 870.6672) 
(list 3200.5254 870.6775) 
(list 3200.5254 870.6878) 
(list 3200.5254 870.6981) 
(list 3200.5254 870.7083) 
(list 3200.5254 870.7186) 
(list 3200.5254 870.7289) 
(list 3200.5254 870.7392) 
(list 3200.5254 870.7494) 
(list 3200.5254 870.7597) 
(list 3200.5254 870.77) 
(list 3201.131 870.77)))
(apply 'command (append '("pline") coords '("c")))
(setq tap10 (ssadd (entlast) tap10))
(command "_mirror" (entlast) "" "3200,900" "3200,901" "No")
(setq tap10 (ssadd (entlast) tap10))
(setq coords (list 
(list 3200 870.77) 
(list 3200.135 870.77) 
(list 3200.135 870.7803) 
(list 3200.135 870.7906) 
(list 3200.135 870.8008) 
(list 3200.135 870.8111) 
(list 3200.135 870.8214) 
(list 3200.135 870.8317) 
(list 3200.135 870.8419) 
(list 3200.135 870.8522) 
(list 3200.135 870.8625) 
(list 3200.135 870.8728) 
(list 3200.135 870.8831) 
(list 3200.135 870.8933) 
(list 3200.135 870.9036) 
(list 3200.135 870.9139) 
(list 3200.135 870.9242) 
(list 3200.135 870.9344) 
(list 3200.135 870.9447) 
(list 3200.135 870.955) 
(list 3200.135 870.9653) 
(list 3200.135 870.9756) 
(list 3200.135 870.9858) 
(list 3200.135 870.9961) 
(list 3200.135 871.0064) 
(list 3200.135 871.0167) 
(list 3200.135 871.0269) 
(list 3200.135 871.0372) 
(list 3200.135 871.0475) 
(list 3200.135 871.0578) 
(list 3200.135 871.0681) 
(list 3200.135 871.0783) 
(list 3200.135 871.0886) 
(list 3200.135 871.0989) 
(list 3200.135 871.1092) 
(list 3200.135 871.1194) 
(list 3200.135 871.1297) 
(list 3200.135 871.14) 
(list 3200 871.14)))
(apply 'command (append '("pline") coords '("c")))
(setq tap10 (ssadd (entlast) tap10))
(command "_mirror" (entlast) "" "3200,900" "3200,901" "No")
(setq tap10 (ssadd (entlast) tap10))
(setq coords (list 
(list 3200.5354 870.77) 
(list 3200.5254 870.77) 
(list 3200.5241 870.7803) 
(list 3200.5199 870.7906) 
(list 3200.5129 870.8008) 
(list 3200.5032 870.8111) 
(list 3200.4911 870.8214) 
(list 3200.477 870.8317) 
(list 3200.4613 870.8419) 
(list 3200.4444 870.8522) 
(list 3200.427 870.8625) 
(list 3200.4095 870.8728) 
(list 3200.3924 870.8831) 
(list 3200.3763 870.8933) 
(list 3200.3616 870.9036) 
(list 3200.3489 870.9139) 
(list 3200.3385 870.9242) 
(list 3200.3308 870.9344) 
(list 3200.3259 870.9447) 
(list 3200.3241 870.955) 
(list 3200.3255 870.9653) 
(list 3200.33 870.9756) 
(list 3200.3374 870.9858) 
(list 3200.3476 870.9961) 
(list 3200.3603 871.0064) 
(list 3200.3751 871.0167) 
(list 3200.3916 871.0269) 
(list 3200.4093 871.0372) 
(list 3200.4275 871.0475) 
(list 3200.4459 871.0578) 
(list 3200.4638 871.0681) 
(list 3200.4807 871.0783) 
(list 3200.496 871.0886) 
(list 3200.5093 871.0989) 
(list 3200.5202 871.1092) 
(list 3200.5284 871.1194) 
(list 3200.5335 871.1297) 
(list 3200.5354 871.14) 
(list 3200.5354 871.14)))
(apply 'command (append '("pline") coords '("c")))
(setq tap10 (ssadd (entlast) tap10))
(command "_mirror" (entlast) "" "3200,900" "3200,901" "No")
(setq tap10 (ssadd (entlast) tap10))
(setq coords (list 
(list 3201.131 870.77) 
(list 3200.5354 870.77) 
(list 3200.5354 870.7803) 
(list 3200.5354 870.7906) 
(list 3200.5354 870.8008) 
(list 3200.5354 870.8111) 
(list 3200.5354 870.8214) 
(list 3200.5354 870.8317) 
(list 3200.5354 870.8419) 
(list 3200.5354 870.8522) 
(list 3200.5354 870.8625) 
(list 3200.5354 870.8728) 
(list 3200.5354 870.8831) 
(list 3200.5354 870.8933) 
(list 3200.5354 870.9036) 
(list 3200.5354 870.9139) 
(list 3200.5354 870.9242) 
(list 3200.5354 870.9344) 
(list 3200.5354 870.9447) 
(list 3200.5354 870.955) 
(list 3200.5354 870.9653) 
(list 3200.5354 870.9756) 
(list 3200.5354 870.9858) 
(list 3200.5354 870.9961) 
(list 3200.5354 871.0064) 
(list 3200.5354 871.0167) 
(list 3200.5354 871.0269) 
(list 3200.5354 871.0372) 
(list 3200.5354 871.0475) 
(list 3200.5354 871.0578) 
(list 3200.5354 871.0681) 
(list 3200.5354 871.0783) 
(list 3200.5354 871.0886) 
(list 3200.5354 871.0989) 
(list 3200.5354 871.1092) 
(list 3200.5354 871.1194) 
(list 3200.5354 871.1297) 
(list 3200.5354 871.14) 
(list 3201.131 871.14)))
(apply 'command (append '("pline") coords '("c")))
(setq tap10 (ssadd (entlast) tap10))
(command "_mirror" (entlast) "" "3200,900" "3200,901" "No")
(setq tap10 (ssadd (entlast) tap10))
(setq coords (list 
(list 3200 871.14) 
(list 3200.135 871.14) 
(list 3200.135 871.1503) 
(list 3200.135 871.1606) 
(list 3200.135 871.1708) 
(list 3200.135 871.1811) 
(list 3200.135 871.1914) 
(list 3200.135 871.2017) 
(list 3200.135 871.2119) 
(list 3200.135 871.2222) 
(list 3200.135 871.2325) 
(list 3200.135 871.2428) 
(list 3200.135 871.2531) 
(list 3200.135 871.2633) 
(list 3200.135 871.2736) 
(list 3200.135 871.2839) 
(list 3200.135 871.2942) 
(list 3200.135 871.3044) 
(list 3200.135 871.3147) 
(list 3200.135 871.325) 
(list 3200.135 871.3353) 
(list 3200.135 871.3456) 
(list 3200.135 871.3558) 
(list 3200.135 871.3661) 
(list 3200.135 871.3764) 
(list 3200.135 871.3867) 
(list 3200.135 871.3969) 
(list 3200.135 871.4072) 
(list 3200.135 871.4175) 
(list 3200.135 871.4278) 
(list 3200.135 871.4381) 
(list 3200.135 871.4483) 
(list 3200.135 871.4586) 
(list 3200.135 871.4689) 
(list 3200.135 871.4792) 
(list 3200.135 871.4894) 
(list 3200.135 871.4997) 
(list 3200.135 871.51) 
(list 3200 871.51)))
(apply 'command (append '("pline") coords '("c")))
(setq tap10 (ssadd (entlast) tap10))
(command "_mirror" (entlast) "" "3200,900" "3200,901" "No")
(setq tap10 (ssadd (entlast) tap10))
(setq coords (list 
(list 3200.5454 871.14) 
(list 3200.5354 871.14) 
(list 3200.534 871.1503) 
(list 3200.5294 871.1606) 
(list 3200.5217 871.1708) 
(list 3200.5111 871.1811) 
(list 3200.4979 871.1914) 
(list 3200.4825 871.2017) 
(list 3200.4654 871.2119) 
(list 3200.4471 871.2222) 
(list 3200.4281 871.2325) 
(list 3200.409 871.2428) 
(list 3200.3904 871.2531) 
(list 3200.3729 871.2633) 
(list 3200.3569 871.2736) 
(list 3200.3431 871.2839) 
(list 3200.3318 871.2942) 
(list 3200.3234 871.3044) 
(list 3200.3182 871.3147) 
(list 3200.3162 871.325) 
(list 3200.3177 871.3353) 
(list 3200.3226 871.3456) 
(list 3200.3307 871.3558) 
(list 3200.3418 871.3661) 
(list 3200.3556 871.3764) 
(list 3200.3717 871.3867) 
(list 3200.3896 871.3969) 
(list 3200.4088 871.4072) 
(list 3200.4286 871.4175) 
(list 3200.4485 871.4278) 
(list 3200.4679 871.4381) 
(list 3200.4862 871.4483) 
(list 3200.5028 871.4586) 
(list 3200.5173 871.4689) 
(list 3200.5291 871.4792) 
(list 3200.5379 871.4894) 
(list 3200.5434 871.4997) 
(list 3200.5454 871.51) 
(list 3200.5454 871.51)))
(apply 'command (append '("pline") coords '("c")))
(setq tap10 (ssadd (entlast) tap10))
(command "_mirror" (entlast) "" "3200,900" "3200,901" "No")
(setq tap10 (ssadd (entlast) tap10))
(setq coords (list 
(list 3201.131 871.14) 
(list 3200.5454 871.14) 
(list 3200.5454 871.1503) 
(list 3200.5454 871.1606) 
(list 3200.5454 871.1708) 
(list 3200.5454 871.1811) 
(list 3200.5454 871.1914) 
(list 3200.5454 871.2017) 
(list 3200.5454 871.2119) 
(list 3200.5454 871.2222) 
(list 3200.5454 871.2325) 
(list 3200.5454 871.2428) 
(list 3200.5454 871.2531) 
(list 3200.5454 871.2633) 
(list 3200.5454 871.2736) 
(list 3200.5454 871.2839) 
(list 3200.5454 871.2942) 
(list 3200.5454 871.3044) 
(list 3200.5454 871.3147) 
(list 3200.5454 871.325) 
(list 3200.5454 871.3353) 
(list 3200.5454 871.3456) 
(list 3200.5454 871.3558) 
(list 3200.5454 871.3661) 
(list 3200.5454 871.3764) 
(list 3200.5454 871.3867) 
(list 3200.5454 871.3969) 
(list 3200.5454 871.4072) 
(list 3200.5454 871.4175) 
(list 3200.5454 871.4278) 
(list 3200.5454 871.4381) 
(list 3200.5454 871.4483) 
(list 3200.5454 871.4586) 
(list 3200.5454 871.4689) 
(list 3200.5454 871.4792) 
(list 3200.5454 871.4894) 
(list 3200.5454 871.4997) 
(list 3200.5454 871.51) 
(list 3201.131 871.51)))
(apply 'command (append '("pline") coords '("c")))
(setq tap10 (ssadd (entlast) tap10))
(command "_mirror" (entlast) "" "3200,900" "3200,901" "No")
(setq tap10 (ssadd (entlast) tap10))
(setq coords (list 
(list 3200 871.51) 
(list 3200.135 871.51) 
(list 3200.135 871.5203) 
(list 3200.135 871.5306) 
(list 3200.135 871.5408) 
(list 3200.135 871.5511) 
(list 3200.135 871.5614) 
(list 3200.135 871.5717) 
(list 3200.135 871.5819) 
(list 3200.135 871.5922) 
(list 3200.135 871.6025) 
(list 3200.135 871.6128) 
(list 3200.135 871.6231) 
(list 3200.135 871.6333) 
(list 3200.135 871.6436) 
(list 3200.135 871.6539) 
(list 3200.135 871.6642) 
(list 3200.135 871.6744) 
(list 3200.135 871.6847) 
(list 3200.135 871.695) 
(list 3200.135 871.7053) 
(list 3200.135 871.7156) 
(list 3200.135 871.7258) 
(list 3200.135 871.7361) 
(list 3200.135 871.7464) 
(list 3200.135 871.7567) 
(list 3200.135 871.7669) 
(list 3200.135 871.7772) 
(list 3200.135 871.7875) 
(list 3200.135 871.7978) 
(list 3200.135 871.8081) 
(list 3200.135 871.8183) 
(list 3200.135 871.8286) 
(list 3200.135 871.8389) 
(list 3200.135 871.8492) 
(list 3200.135 871.8594) 
(list 3200.135 871.8697) 
(list 3200.135 871.88) 
(list 3200 871.88)))
(apply 'command (append '("pline") coords '("c")))
(setq tap10 (ssadd (entlast) tap10))
(command "_mirror" (entlast) "" "3200,900" "3200,901" "No")
(setq tap10 (ssadd (entlast) tap10))
(setq coords (list 
(list 3200.5555 871.51) 
(list 3200.5454 871.51) 
(list 3200.5439 871.5203) 
(list 3200.5389 871.5306) 
(list 3200.5306 871.5408) 
(list 3200.519 871.5511) 
(list 3200.5047 871.5614) 
(list 3200.4881 871.5717) 
(list 3200.4695 871.5819) 
(list 3200.4497 871.5922) 
(list 3200.4291 871.6025) 
(list 3200.4085 871.6128) 
(list 3200.3884 871.6231) 
(list 3200.3694 871.6333) 
(list 3200.3522 871.6436) 
(list 3200.3373 871.6539) 
(list 3200.3251 871.6642) 
(list 3200.3161 871.6744) 
(list 3200.3104 871.6847) 
(list 3200.3083 871.695) 
(list 3200.31 871.7053) 
(list 3200.3152 871.7156) 
(list 3200.324 871.7258) 
(list 3200.336 871.7361) 
(list 3200.3509 871.7464) 
(list 3200.3683 871.7567) 
(list 3200.3876 871.7669) 
(list 3200.4083 871.7772) 
(list 3200.4297 871.7875) 
(list 3200.4511 871.7978) 
(list 3200.4721 871.8081) 
(list 3200.4918 871.8183) 
(list 3200.5097 871.8286) 
(list 3200.5252 871.8389) 
(list 3200.5379 871.8492) 
(list 3200.5474 871.8594) 
(list 3200.5533 871.8697) 
(list 3200.5555 871.88) 
(list 3200.5555 871.88)))
(apply 'command (append '("pline") coords '("c")))
(setq tap10 (ssadd (entlast) tap10))
(command "_mirror" (entlast) "" "3200,900" "3200,901" "No")
(setq tap10 (ssadd (entlast) tap10))
(setq coords (list 
(list 3201.131 871.51) 
(list 3200.5555 871.51) 
(list 3200.5555 871.5203) 
(list 3200.5555 871.5306) 
(list 3200.5555 871.5408) 
(list 3200.5555 871.5511) 
(list 3200.5555 871.5614) 
(list 3200.5555 871.5717) 
(list 3200.5555 871.5819) 
(list 3200.5555 871.5922) 
(list 3200.5555 871.6025) 
(list 3200.5555 871.6128) 
(list 3200.5555 871.6231) 
(list 3200.5555 871.6333) 
(list 3200.5555 871.6436) 
(list 3200.5555 871.6539) 
(list 3200.5555 871.6642) 
(list 3200.5555 871.6744) 
(list 3200.5555 871.6847) 
(list 3200.5555 871.695) 
(list 3200.5555 871.7053) 
(list 3200.5555 871.7156) 
(list 3200.5555 871.7258) 
(list 3200.5555 871.7361) 
(list 3200.5555 871.7464) 
(list 3200.5555 871.7567) 
(list 3200.5555 871.7669) 
(list 3200.5555 871.7772) 
(list 3200.5555 871.7875) 
(list 3200.5555 871.7978) 
(list 3200.5555 871.8081) 
(list 3200.5555 871.8183) 
(list 3200.5555 871.8286) 
(list 3200.5555 871.8389) 
(list 3200.5555 871.8492) 
(list 3200.5555 871.8594) 
(list 3200.5555 871.8697) 
(list 3200.5555 871.88) 
(list 3201.131 871.88)))
(apply 'command (append '("pline") coords '("c")))
(setq tap10 (ssadd (entlast) tap10))
(command "_mirror" (entlast) "" "3200,900" "3200,901" "No")
(setq tap10 (ssadd (entlast) tap10))
(setq coords (list 
(list 3200 871.88) 
(list 3200.135 871.88) 
(list 3200.135 871.8903) 
(list 3200.135 871.9006) 
(list 3200.135 871.9108) 
(list 3200.135 871.9211) 
(list 3200.135 871.9314) 
(list 3200.135 871.9417) 
(list 3200.135 871.9519) 
(list 3200.135 871.9622) 
(list 3200.135 871.9725) 
(list 3200.135 871.9828) 
(list 3200.135 871.9931) 
(list 3200.135 872.0033) 
(list 3200.135 872.0136) 
(list 3200.135 872.0239) 
(list 3200.135 872.0342) 
(list 3200.135 872.0444) 
(list 3200.135 872.0547) 
(list 3200.135 872.065) 
(list 3200.135 872.0753) 
(list 3200.135 872.0856) 
(list 3200.135 872.0958) 
(list 3200.135 872.1061) 
(list 3200.135 872.1164) 
(list 3200.135 872.1267) 
(list 3200.135 872.1369) 
(list 3200.135 872.1472) 
(list 3200.135 872.1575) 
(list 3200.135 872.1678) 
(list 3200.135 872.1781) 
(list 3200.135 872.1883) 
(list 3200.135 872.1986) 
(list 3200.135 872.2089) 
(list 3200.135 872.2192) 
(list 3200.135 872.2294) 
(list 3200.135 872.2397) 
(list 3200.135 872.25) 
(list 3200 872.25)))
(apply 'command (append '("pline") coords '("c")))
(setq tap10 (ssadd (entlast) tap10))
(command "_mirror" (entlast) "" "3200,900" "3200,901" "No")
(setq tap10 (ssadd (entlast) tap10))
(setq coords (list 
(list 3200.5655 871.88) 
(list 3200.5555 871.88) 
(list 3200.5538 871.8903) 
(list 3200.5484 871.9006) 
(list 3200.5394 871.9108) 
(list 3200.527 871.9211) 
(list 3200.5116 871.9314) 
(list 3200.4936 871.9417) 
(list 3200.4737 871.9519) 
(list 3200.4523 871.9622) 
(list 3200.4302 871.9725) 
(list 3200.408 871.9828) 
(list 3200.3864 871.9931) 
(list 3200.366 872.0033) 
(list 3200.3475 872.0136) 
(list 3200.3315 872.0239) 
(list 3200.3184 872.0342) 
(list 3200.3087 872.0444) 
(list 3200.3026 872.0547) 
(list 3200.3005 872.065) 
(list 3200.3022 872.0753) 
(list 3200.3079 872.0856) 
(list 3200.3173 872.0958) 
(list 3200.3302 872.1061) 
(list 3200.3462 872.1164) 
(list 3200.3649 872.1267) 
(list 3200.3856 872.1369) 
(list 3200.4078 872.1472) 
(list 3200.4307 872.1575) 
(list 3200.4538 872.1678) 
(list 3200.4762 872.1781) 
(list 3200.4973 872.1883) 
(list 3200.5165 872.1986) 
(list 3200.5332 872.2089) 
(list 3200.5467 872.2192) 
(list 3200.5569 872.2294) 
(list 3200.5632 872.2397) 
(list 3200.5655 872.25) 
(list 3200.5655 872.25)))
(apply 'command (append '("pline") coords '("c")))
(setq tap10 (ssadd (entlast) tap10))
(command "_mirror" (entlast) "" "3200,900" "3200,901" "No")
(setq tap10 (ssadd (entlast) tap10))
(setq coords (list 
(list 3201.131 871.88) 
(list 3200.5655 871.88) 
(list 3200.5655 871.8903) 
(list 3200.5655 871.9006) 
(list 3200.5655 871.9108) 
(list 3200.5655 871.9211) 
(list 3200.5655 871.9314) 
(list 3200.5655 871.9417) 
(list 3200.5655 871.9519) 
(list 3200.5655 871.9622) 
(list 3200.5655 871.9725) 
(list 3200.5655 871.9828) 
(list 3200.5655 871.9931) 
(list 3200.5655 872.0033) 
(list 3200.5655 872.0136) 
(list 3200.5655 872.0239) 
(list 3200.5655 872.0342) 
(list 3200.5655 872.0444) 
(list 3200.5655 872.0547) 
(list 3200.5655 872.065) 
(list 3200.5655 872.0753) 
(list 3200.5655 872.0856) 
(list 3200.5655 872.0958) 
(list 3200.5655 872.1061) 
(list 3200.5655 872.1164) 
(list 3200.5655 872.1267) 
(list 3200.5655 872.1369) 
(list 3200.5655 872.1472) 
(list 3200.5655 872.1575) 
(list 3200.5655 872.1678) 
(list 3200.5655 872.1781) 
(list 3200.5655 872.1883) 
(list 3200.5655 872.1986) 
(list 3200.5655 872.2089) 
(list 3200.5655 872.2192) 
(list 3200.5655 872.2294) 
(list 3200.5655 872.2397) 
(list 3200.5655 872.25) 
(list 3201.131 872.25)))
(apply 'command (append '("pline") coords '("c")))
(setq tap10 (ssadd (entlast) tap10))
(command "_mirror" (entlast) "" "3200,900" "3200,901" "No")
(setq tap10 (ssadd (entlast) tap10))
(command "_block" "blktap10" "3200,900" tap10 "")
(command "_insert" "blktap10" "3200,900" "1" "1" "0")
(command "_insert" "blktap10" "3200,900" "1" "1" "180")
(setq uc10 nil)
(setq uc10 (ssadd))
(setq coords (list 
(list 0 -0.185) 
(list 0.135 -0.185) 
(list 0.135 -0.17472) 
(list 0.135 -0.16444) 
(list 0.135 -0.15417) 
(list 0.135 -0.14389) 
(list 0.135 -0.13361) 
(list 0.135 -0.12333) 
(list 0.135 -0.11306) 
(list 0.135 -0.10278) 
(list 0.135 -0.0925) 
(list 0.135 -0.082222) 
(list 0.135 -0.071944) 
(list 0.135 -0.061667) 
(list 0.135 -0.051389) 
(list 0.135 -0.041111) 
(list 0.135 -0.030833) 
(list 0.135 -0.020556) 
(list 0.135 -0.010278) 
(list 0.135 0) 
(list 0.135 0.010278) 
(list 0.135 0.020556) 
(list 0.135 0.030833) 
(list 0.135 0.041111) 
(list 0.135 0.051389) 
(list 0.135 0.061667) 
(list 0.135 0.071944) 
(list 0.135 0.082222) 
(list 0.135 0.0925) 
(list 0.135 0.10278) 
(list 0.135 0.11306) 
(list 0.135 0.12333) 
(list 0.135 0.13361) 
(list 0.135 0.14389) 
(list 0.135 0.15417) 
(list 0.135 0.16444) 
(list 0.135 0.17472) 
(list 0.135 0.185) 
(list 0 0.185)))
(apply 'command (append '("pline") coords '("c")))
(setq uc10 (ssadd (entlast) uc10))
(setq coords (list 
(list 1.131 -0.185) 
(list 0.5655 -0.185) 
(list 0.56346 -0.17472) 
(list 0.55739 -0.16444) 
(list 0.54748 -0.15417) 
(list 0.53403 -0.14389) 
(list 0.51745 -0.13361) 
(list 0.49825 -0.12333) 
(list 0.477 -0.11306) 
(list 0.45436 -0.10278) 
(list 0.431 -0.0925) 
(list 0.40764 -0.082222) 
(list 0.385 -0.071944) 
(list 0.36375 -0.061667) 
(list 0.34454 -0.051389) 
(list 0.32797 -0.041111) 
(list 0.31452 -0.030833) 
(list 0.30461 -0.020556) 
(list 0.29854 -0.010278) 
(list 0.2965 0) 
(list 0.29854 0.010278) 
(list 0.30461 0.020556) 
(list 0.31452 0.030833) 
(list 0.32797 0.041111) 
(list 0.34454 0.051389) 
(list 0.36375 0.061667) 
(list 0.385 0.071944) 
(list 0.40764 0.082222) 
(list 0.431 0.0925) 
(list 0.45436 0.10278) 
(list 0.477 0.11306) 
(list 0.49825 0.12333) 
(list 0.51745 0.13361) 
(list 0.53403 0.14389) 
(list 0.54748 0.15417) 
(list 0.55739 0.16444) 
(list 0.56346 0.17472) 
(list 0.5655 0.185) 
(list 1.131 0.185)))
(apply 'command (append '("pline") coords '("c")))
(setq uc10 (ssadd (entlast) uc10))
(command "_block" "blkuc10" "0,0.185" uc10 "")
(command "_insert" "blkuc10" "3200,872.62" "1" "1" "0")
(command "_insert" "blkuc10" "3200,872.25" "1" "1" "180")
(command "_insert" "blkuc10" "3200,872.99" "1" "1" "0")
(command "_insert" "blkuc10" "3200,872.62" "1" "1" "180")
(command "_insert" "blkuc10" "3200,873.36" "1" "1" "0")
(command "_insert" "blkuc10" "3200,872.99" "1" "1" "180")
(command "_insert" "blkuc10" "3200,873.73" "1" "1" "0")
(command "_insert" "blkuc10" "3200,873.36" "1" "1" "180")
(command "_insert" "blkuc10" "3200,874.1" "1" "1" "0")
(command "_insert" "blkuc10" "3200,873.73" "1" "1" "180")
(command "_insert" "blkuc10" "3200,874.47" "1" "1" "0")
(command "_insert" "blkuc10" "3200,874.1" "1" "1" "180")
(command "_insert" "blkuc10" "3200,874.84" "1" "1" "0")
(command "_insert" "blkuc10" "3200,874.47" "1" "1" "180")
(command "_insert" "blkuc10" "3200,875.21" "1" "1" "0")
(command "_insert" "blkuc10" "3200,874.84" "1" "1" "180")
(command "_insert" "blkuc10" "3200,875.58" "1" "1" "0")
(command "_insert" "blkuc10" "3200,875.21" "1" "1" "180")
(command "_insert" "blkuc10" "3200,875.95" "1" "1" "0")
(command "_insert" "blkuc10" "3200,875.58" "1" "1" "180")
(command "_insert" "blkuc10" "3200,876.32" "1" "1" "0")
(command "_insert" "blkuc10" "3200,875.95" "1" "1" "180")
(command "_insert" "blkuc10" "3200,876.69" "1" "1" "0")
(command "_insert" "blkuc10" "3200,876.32" "1" "1" "180")
(command "_insert" "blkuc10" "3200,877.06" "1" "1" "0")
(command "_insert" "blkuc10" "3200,876.69" "1" "1" "180")
(command "_insert" "blkuc10" "3200,877.43" "1" "1" "0")
(command "_insert" "blkuc10" "3200,877.06" "1" "1" "180")
(command "_insert" "blkuc10" "3200,877.8" "1" "1" "0")
(command "_insert" "blkuc10" "3200,877.43" "1" "1" "180")
(command "_insert" "blkuc10" "3200,878.17" "1" "1" "0")
(command "_insert" "blkuc10" "3200,877.8" "1" "1" "180")
(command "_insert" "blkuc10" "3200,878.54" "1" "1" "0")
(command "_insert" "blkuc10" "3200,878.17" "1" "1" "180")
(command "_insert" "blkuc10" "3200,878.91" "1" "1" "0")
(command "_insert" "blkuc10" "3200,878.54" "1" "1" "180")
(command "_insert" "blkuc10" "3200,879.28" "1" "1" "0")
(command "_insert" "blkuc10" "3200,878.91" "1" "1" "180")
(command "_insert" "blkuc10" "3200,879.65" "1" "1" "0")
(command "_insert" "blkuc10" "3200,879.28" "1" "1" "180")
(command "_insert" "blkuc10" "3200,880.02" "1" "1" "0")
(command "_insert" "blkuc10" "3200,879.65" "1" "1" "180")
(command "_insert" "blkuc10" "3200,880.39" "1" "1" "0")
(command "_insert" "blkuc10" "3200,880.02" "1" "1" "180")
(command "_insert" "blkuc10" "3200,880.76" "1" "1" "0")
(command "_insert" "blkuc10" "3200,880.39" "1" "1" "180")
(command "_insert" "blkuc10" "3200,881.13" "1" "1" "0")
(command "_insert" "blkuc10" "3200,880.76" "1" "1" "180")
(command "_insert" "blkuc10" "3200,881.5" "1" "1" "0")
(command "_insert" "blkuc10" "3200,881.13" "1" "1" "180")
(command "_insert" "blkuc10" "3200,881.87" "1" "1" "0")
(command "_insert" "blkuc10" "3200,881.5" "1" "1" "180")
(command "_insert" "blkuc10" "3200,882.24" "1" "1" "0")
(command "_insert" "blkuc10" "3200,881.87" "1" "1" "180")
(command "_insert" "blkuc10" "3200,882.61" "1" "1" "0")
(command "_insert" "blkuc10" "3200,882.24" "1" "1" "180")
(command "_insert" "blkuc10" "3200,882.98" "1" "1" "0")
(command "_insert" "blkuc10" "3200,882.61" "1" "1" "180")
(command "_insert" "blkuc10" "3200,883.35" "1" "1" "0")
(command "_insert" "blkuc10" "3200,882.98" "1" "1" "180")
(command "_insert" "blkuc10" "3200,883.72" "1" "1" "0")
(command "_insert" "blkuc10" "3200,883.35" "1" "1" "180")
(command "_insert" "blkuc10" "3200,884.09" "1" "1" "0")
(command "_insert" "blkuc10" "3200,883.72" "1" "1" "180")
(command "_insert" "blkuc10" "3200,884.46" "1" "1" "0")
(command "_insert" "blkuc10" "3200,884.09" "1" "1" "180")
(command "_insert" "blkuc10" "3200,884.83" "1" "1" "0")
(command "_insert" "blkuc10" "3200,884.46" "1" "1" "180")
(command "_insert" "blkuc10" "3200,885.2" "1" "1" "0")
(command "_insert" "blkuc10" "3200,884.83" "1" "1" "180")
(command "_insert" "blkuc10" "3200,885.57" "1" "1" "0")
(command "_insert" "blkuc10" "3200,885.2" "1" "1" "180")
(command "_insert" "blkuc10" "3200,885.94" "1" "1" "0")
(command "_insert" "blkuc10" "3200,885.57" "1" "1" "180")
(command "_insert" "blkuc10" "3200,886.31" "1" "1" "0")
(command "_insert" "blkuc10" "3200,885.94" "1" "1" "180")
(command "_insert" "blkuc10" "3200,886.68" "1" "1" "0")
(command "_insert" "blkuc10" "3200,886.31" "1" "1" "180")
(command "_insert" "blkuc10" "3200,887.05" "1" "1" "0")
(command "_insert" "blkuc10" "3200,886.68" "1" "1" "180")
(command "_insert" "blkuc10" "3200,887.42" "1" "1" "0")
(command "_insert" "blkuc10" "3200,887.05" "1" "1" "180")
(command "_insert" "blkuc10" "3200,887.79" "1" "1" "0")
(command "_insert" "blkuc10" "3200,887.42" "1" "1" "180")
(command "_insert" "blkuc10" "3200,888.16" "1" "1" "0")
(command "_insert" "blkuc10" "3200,887.79" "1" "1" "180")
(command "_insert" "blkuc10" "3200,888.53" "1" "1" "0")
(command "_insert" "blkuc10" "3200,888.16" "1" "1" "180")
(command "_insert" "blkuc10" "3200,888.9" "1" "1" "0")
(command "_insert" "blkuc10" "3200,888.53" "1" "1" "180")
(command "_insert" "blkuc10" "3200,889.27" "1" "1" "0")
(command "_insert" "blkuc10" "3200,888.9" "1" "1" "180")
(command "_insert" "blkuc10" "3200,889.64" "1" "1" "0")
(command "_insert" "blkuc10" "3200,889.27" "1" "1" "180")
(command "_insert" "blkuc10" "3200,890.01" "1" "1" "0")
(command "_insert" "blkuc10" "3200,889.64" "1" "1" "180")
(command "_insert" "blkuc10" "3200,890.38" "1" "1" "0")
(command "_insert" "blkuc10" "3200,890.01" "1" "1" "180")
(command "_insert" "blkuc10" "3200,890.75" "1" "1" "0")
(command "_insert" "blkuc10" "3200,890.38" "1" "1" "180")
(command "_insert" "blkuc10" "3200,891.12" "1" "1" "0")
(command "_insert" "blkuc10" "3200,890.75" "1" "1" "180")
(command "_insert" "blkuc10" "3200,891.49" "1" "1" "0")
(command "_insert" "blkuc10" "3200,891.12" "1" "1" "180")
(command "_insert" "blkuc10" "3200,891.86" "1" "1" "0")
(command "_insert" "blkuc10" "3200,891.49" "1" "1" "180")
(command "_insert" "blkuc10" "3200,892.23" "1" "1" "0")
(command "_insert" "blkuc10" "3200,891.86" "1" "1" "180")
(command "_insert" "blkuc10" "3200,892.6" "1" "1" "0")
(command "_insert" "blkuc10" "3200,892.23" "1" "1" "180")
(command "_insert" "blkuc10" "3200,892.97" "1" "1" "0")
(command "_insert" "blkuc10" "3200,892.6" "1" "1" "180")
(command "_insert" "blkuc10" "3200,893.34" "1" "1" "0")
(command "_insert" "blkuc10" "3200,892.97" "1" "1" "180")
(command "_insert" "blkuc10" "3200,893.71" "1" "1" "0")
(command "_insert" "blkuc10" "3200,893.34" "1" "1" "180")
(command "_insert" "blkuc10" "3200,894.08" "1" "1" "0")
(command "_insert" "blkuc10" "3200,893.71" "1" "1" "180")
(command "_insert" "blkuc10" "3200,894.45" "1" "1" "0")
(command "_insert" "blkuc10" "3200,894.08" "1" "1" "180")
(command "_insert" "blkuc10" "3200,894.82" "1" "1" "0")
(command "_insert" "blkuc10" "3200,894.45" "1" "1" "180")
(command "_insert" "blkuc10" "3200,895.19" "1" "1" "0")
(command "_insert" "blkuc10" "3200,894.82" "1" "1" "180")
(command "_insert" "blkuc10" "3200,895.56" "1" "1" "0")
(command "_insert" "blkuc10" "3200,895.19" "1" "1" "180")
(command "_insert" "blkuc10" "3200,895.93" "1" "1" "0")
(command "_insert" "blkuc10" "3200,895.56" "1" "1" "180")
(command "_insert" "blkuc10" "3200,896.3" "1" "1" "0")
(command "_insert" "blkuc10" "3200,895.93" "1" "1" "180")
(command "_insert" "blkuc10" "3200,896.67" "1" "1" "0")
(command "_insert" "blkuc10" "3200,896.3" "1" "1" "180")
(command "_insert" "blkuc10" "3200,897.04" "1" "1" "0")
(command "_insert" "blkuc10" "3200,896.67" "1" "1" "180")
(command "_insert" "blkuc10" "3200,897.41" "1" "1" "0")
(command "_insert" "blkuc10" "3200,897.04" "1" "1" "180")
(command "_insert" "blkuc10" "3200,897.78" "1" "1" "0")
(command "_insert" "blkuc10" "3200,897.41" "1" "1" "180")
(command "_insert" "blkuc10" "3200,898.15" "1" "1" "0")
(command "_insert" "blkuc10" "3200,897.78" "1" "1" "180")
(command "_insert" "blkuc10" "3200,898.52" "1" "1" "0")
(command "_insert" "blkuc10" "3200,898.15" "1" "1" "180")
(command "_insert" "blkuc10" "3200,898.89" "1" "1" "0")
(command "_insert" "blkuc10" "3200,898.52" "1" "1" "180")
(command "_insert" "blkuc10" "3200,899.26" "1" "1" "0")
(command "_insert" "blkuc10" "3200,898.89" "1" "1" "180")
(command "_insert" "blkuc10" "3200,899.63" "1" "1" "0")
(command "_insert" "blkuc10" "3200,899.26" "1" "1" "180")
(command "_insert" "blkuc10" "3200,900" "1" "1" "0")
(command "_insert" "blkuc10" "3200,899.63" "1" "1" "180")
(command "_insert" "blkuc10" "3200,900.37" "1" "1" "0")
(command "_insert" "blkuc10" "3200,900" "1" "1" "180")
(command "_insert" "blkuc10" "3200,900.74" "1" "1" "0")
(command "_insert" "blkuc10" "3200,900.37" "1" "1" "180")
(command "_insert" "blkuc10" "3200,901.11" "1" "1" "0")
(command "_insert" "blkuc10" "3200,900.74" "1" "1" "180")
(command "_insert" "blkuc10" "3200,901.48" "1" "1" "0")
(command "_insert" "blkuc10" "3200,901.11" "1" "1" "180")
(command "_insert" "blkuc10" "3200,901.85" "1" "1" "0")
(command "_insert" "blkuc10" "3200,901.48" "1" "1" "180")
(command "_insert" "blkuc10" "3200,902.22" "1" "1" "0")
(command "_insert" "blkuc10" "3200,901.85" "1" "1" "180")
(command "_insert" "blkuc10" "3200,902.59" "1" "1" "0")
(command "_insert" "blkuc10" "3200,902.22" "1" "1" "180")
(command "_insert" "blkuc10" "3200,902.96" "1" "1" "0")
(command "_insert" "blkuc10" "3200,902.59" "1" "1" "180")
(command "_insert" "blkuc10" "3200,903.33" "1" "1" "0")
(command "_insert" "blkuc10" "3200,902.96" "1" "1" "180")
(command "_insert" "blkuc10" "3200,903.7" "1" "1" "0")
(command "_insert" "blkuc10" "3200,903.33" "1" "1" "180")
(command "_insert" "blkuc10" "3200,904.07" "1" "1" "0")
(command "_insert" "blkuc10" "3200,903.7" "1" "1" "180")
(command "_insert" "blkuc10" "3200,904.44" "1" "1" "0")
(command "_insert" "blkuc10" "3200,904.07" "1" "1" "180")
(command "_insert" "blkuc10" "3200,904.81" "1" "1" "0")
(command "_insert" "blkuc10" "3200,904.44" "1" "1" "180")
(command "_insert" "blkuc10" "3200,905.18" "1" "1" "0")
(command "_insert" "blkuc10" "3200,904.81" "1" "1" "180")
(command "_insert" "blkuc10" "3200,905.55" "1" "1" "0")
(command "_insert" "blkuc10" "3200,905.18" "1" "1" "180")
(command "_insert" "blkuc10" "3200,905.92" "1" "1" "0")
(command "_insert" "blkuc10" "3200,905.55" "1" "1" "180")
(command "_insert" "blkuc10" "3200,906.29" "1" "1" "0")
(command "_insert" "blkuc10" "3200,905.92" "1" "1" "180")
(command "_insert" "blkuc10" "3200,906.66" "1" "1" "0")
(command "_insert" "blkuc10" "3200,906.29" "1" "1" "180")
(command "_insert" "blkuc10" "3200,907.03" "1" "1" "0")
(command "_insert" "blkuc10" "3200,906.66" "1" "1" "180")
(command "_insert" "blkuc10" "3200,907.4" "1" "1" "0")
(command "_insert" "blkuc10" "3200,907.03" "1" "1" "180")
(command "_insert" "blkuc10" "3200,907.77" "1" "1" "0")
(command "_insert" "blkuc10" "3200,907.4" "1" "1" "180")
(command "_insert" "blkuc10" "3200,908.14" "1" "1" "0")
(command "_insert" "blkuc10" "3200,907.77" "1" "1" "180")
(command "_insert" "blkuc10" "3200,908.51" "1" "1" "0")
(command "_insert" "blkuc10" "3200,908.14" "1" "1" "180")
(command "_insert" "blkuc10" "3200,908.88" "1" "1" "0")
(command "_insert" "blkuc10" "3200,908.51" "1" "1" "180")
(command "_insert" "blkuc10" "3200,909.25" "1" "1" "0")
(command "_insert" "blkuc10" "3200,908.88" "1" "1" "180")
(command "_insert" "blkuc10" "3200,909.62" "1" "1" "0")
(command "_insert" "blkuc10" "3200,909.25" "1" "1" "180")
(command "_insert" "blkuc10" "3200,909.99" "1" "1" "0")
(command "_insert" "blkuc10" "3200,909.62" "1" "1" "180")
(command "_insert" "blkuc10" "3200,910.36" "1" "1" "0")
(command "_insert" "blkuc10" "3200,909.99" "1" "1" "180")
(command "_insert" "blkuc10" "3200,910.73" "1" "1" "0")
(command "_insert" "blkuc10" "3200,910.36" "1" "1" "180")
(command "_insert" "blkuc10" "3200,911.1" "1" "1" "0")
(command "_insert" "blkuc10" "3200,910.73" "1" "1" "180")
(command "_insert" "blkuc10" "3200,911.47" "1" "1" "0")
(command "_insert" "blkuc10" "3200,911.1" "1" "1" "180")
(command "_insert" "blkuc10" "3200,911.84" "1" "1" "0")
(command "_insert" "blkuc10" "3200,911.47" "1" "1" "180")
(command "_insert" "blkuc10" "3200,912.21" "1" "1" "0")
(command "_insert" "blkuc10" "3200,911.84" "1" "1" "180")
(command "_insert" "blkuc10" "3200,912.58" "1" "1" "0")
(command "_insert" "blkuc10" "3200,912.21" "1" "1" "180")
(command "_insert" "blkuc10" "3200,912.95" "1" "1" "0")
(command "_insert" "blkuc10" "3200,912.58" "1" "1" "180")
(command "_insert" "blkuc10" "3200,913.32" "1" "1" "0")
(command "_insert" "blkuc10" "3200,912.95" "1" "1" "180")
(command "_insert" "blkuc10" "3200,913.69" "1" "1" "0")
(command "_insert" "blkuc10" "3200,913.32" "1" "1" "180")
(command "_insert" "blkuc10" "3200,914.06" "1" "1" "0")
(command "_insert" "blkuc10" "3200,913.69" "1" "1" "180")
(command "_insert" "blkuc10" "3200,914.43" "1" "1" "0")
(command "_insert" "blkuc10" "3200,914.06" "1" "1" "180")
(command "_insert" "blkuc10" "3200,914.8" "1" "1" "0")
(command "_insert" "blkuc10" "3200,914.43" "1" "1" "180")
(command "_insert" "blkuc10" "3200,915.17" "1" "1" "0")
(command "_insert" "blkuc10" "3200,914.8" "1" "1" "180")
(command "_insert" "blkuc10" "3200,915.54" "1" "1" "0")
(command "_insert" "blkuc10" "3200,915.17" "1" "1" "180")
(command "_insert" "blkuc10" "3200,915.91" "1" "1" "0")
(command "_insert" "blkuc10" "3200,915.54" "1" "1" "180")
(command "_insert" "blkuc10" "3200,916.28" "1" "1" "0")
(command "_insert" "blkuc10" "3200,915.91" "1" "1" "180")
(command "_insert" "blkuc10" "3200,916.65" "1" "1" "0")
(command "_insert" "blkuc10" "3200,916.28" "1" "1" "180")
(command "_insert" "blkuc10" "3200,917.02" "1" "1" "0")
(command "_insert" "blkuc10" "3200,916.65" "1" "1" "180")
(command "_insert" "blkuc10" "3200,917.39" "1" "1" "0")
(command "_insert" "blkuc10" "3200,917.02" "1" "1" "180")
(command "_insert" "blkuc10" "3200,917.76" "1" "1" "0")
(command "_insert" "blkuc10" "3200,917.39" "1" "1" "180")
(command "_insert" "blkuc10" "3200,918.13" "1" "1" "0")
(command "_insert" "blkuc10" "3200,917.76" "1" "1" "180")
(command "_insert" "blkuc10" "3200,918.5" "1" "1" "0")
(command "_insert" "blkuc10" "3200,918.13" "1" "1" "180")
(command "_insert" "blkuc10" "3200,918.87" "1" "1" "0")
(command "_insert" "blkuc10" "3200,918.5" "1" "1" "180")
(command "_insert" "blkuc10" "3200,919.24" "1" "1" "0")
(command "_insert" "blkuc10" "3200,918.87" "1" "1" "180")
(command "_insert" "blkuc10" "3200,919.61" "1" "1" "0")
(command "_insert" "blkuc10" "3200,919.24" "1" "1" "180")
(command "_insert" "blkuc10" "3200,919.98" "1" "1" "0")
(command "_insert" "blkuc10" "3200,919.61" "1" "1" "180")
(command "_insert" "blkuc10" "3200,920.35" "1" "1" "0")
(command "_insert" "blkuc10" "3200,919.98" "1" "1" "180")
(command "_insert" "blkuc10" "3200,920.72" "1" "1" "0")
(command "_insert" "blkuc10" "3200,920.35" "1" "1" "180")
(command "_insert" "blkuc10" "3200,921.09" "1" "1" "0")
(command "_insert" "blkuc10" "3200,920.72" "1" "1" "180")
(command "_insert" "blkuc10" "3200,921.46" "1" "1" "0")
(command "_insert" "blkuc10" "3200,921.09" "1" "1" "180")
(command "_insert" "blkuc10" "3200,921.83" "1" "1" "0")
(command "_insert" "blkuc10" "3200,921.46" "1" "1" "180")
(command "_insert" "blkuc10" "3200,922.2" "1" "1" "0")
(command "_insert" "blkuc10" "3200,921.83" "1" "1" "180")
(command "_insert" "blkuc10" "3200,922.57" "1" "1" "0")
(command "_insert" "blkuc10" "3200,922.2" "1" "1" "180")
(command "_insert" "blkuc10" "3200,922.94" "1" "1" "0")
(command "_insert" "blkuc10" "3200,922.57" "1" "1" "180")
(command "_insert" "blkuc10" "3200,923.31" "1" "1" "0")
(command "_insert" "blkuc10" "3200,922.94" "1" "1" "180")
(command "_insert" "blkuc10" "3200,923.68" "1" "1" "0")
(command "_insert" "blkuc10" "3200,923.31" "1" "1" "180")
(command "_insert" "blkuc10" "3200,924.05" "1" "1" "0")
(command "_insert" "blkuc10" "3200,923.68" "1" "1" "180")
(command "_insert" "blkuc10" "3200,924.42" "1" "1" "0")
(command "_insert" "blkuc10" "3200,924.05" "1" "1" "180")
(command "_insert" "blkuc10" "3200,924.79" "1" "1" "0")
(command "_insert" "blkuc10" "3200,924.42" "1" "1" "180")
(command "_insert" "blkuc10" "3200,925.16" "1" "1" "0")
(command "_insert" "blkuc10" "3200,924.79" "1" "1" "180")
(command "_insert" "blkuc10" "3200,925.53" "1" "1" "0")
(command "_insert" "blkuc10" "3200,925.16" "1" "1" "180")
(command "_insert" "blkuc10" "3200,925.9" "1" "1" "0")
(command "_insert" "blkuc10" "3200,925.53" "1" "1" "180")
(command "_insert" "blkuc10" "3200,926.27" "1" "1" "0")
(command "_insert" "blkuc10" "3200,925.9" "1" "1" "180")
(command "_insert" "blkuc10" "3200,926.64" "1" "1" "0")
(command "_insert" "blkuc10" "3200,926.27" "1" "1" "180")
(command "_insert" "blkuc10" "3200,927.01" "1" "1" "0")
(command "_insert" "blkuc10" "3200,926.64" "1" "1" "180")
(command "_insert" "blkuc10" "3200,927.38" "1" "1" "0")
(command "_insert" "blkuc10" "3200,927.01" "1" "1" "180")
(command "_insert" "blkuc10" "3200,927.75" "1" "1" "0")
(command "_insert" "blkuc10" "3200,927.38" "1" "1" "180")
(command "_layer" "set" "phccover" "")
(command "_rectangle" "3198.869,933.3" "3201.131,866.7")
(command "_layer" "set" "nitride" "")
(setq phc10 currobj)
(command "_layer" "set" "cover" "")
(command "_rectangle" "3198.869,836.7" "3201.131,963.3")
(command "_layer" "set" "nitride" "")
(command "_layer" "set" "text" "")
(command "_circle" "3197.919,846.7" "0.075")
(command "_circle" "3197.544,846.7" "0.15")
(command "_circle" "3197.169,846.7" "0.075")
(command "_circle" "3196.794,846.7" "0.15")
(command "_circle" "3197.919,848.7" "0.075")
(command "_circle" "3197.544,848.7" "0.075")
(command "_circle" "3197.169,848.7" "0.15")
(command "_circle" "3196.794,848.7" "0.15")
(command "_circle" "3197.919,850.7" "0.075")
(command "_circle" "3197.544,850.7" "0.15")
(command "_circle" "3197.169,850.7" "0.15")
(command "_circle" "3196.794,850.7" "0.15")
(command "_circle" "3197.919,852.7" "0.075")
(command "_circle" "3197.544,852.7" "0.075")
(command "_circle" "3197.169,852.7" "0.075")
(command "_circle" "3196.794,852.7" "0.075")
(command "_circle" "3196.419,852.7" "0.15")
(command "_circle" "3197.919,854.7" "0.075")
(command "_circle" "3197.544,854.7" "0.15")
(command "_circle" "3197.169,854.7" "0.075")
(command "_circle" "3196.794,854.7" "0.075")
(command "_circle" "3196.419,854.7" "0.15")
(command "_circle" "3197.919,856.7" "0.075")
(command "_circle" "3197.544,856.7" "0.075")
(command "_circle" "3197.169,856.7" "0.15")
(command "_circle" "3196.794,856.7" "0.075")
(command "_circle" "3196.419,856.7" "0.15")
(command "_circle" "3197.919,858.7" "0.075")
(command "_circle" "3197.544,858.7" "0.15")
(command "_circle" "3197.169,858.7" "0.15")
(command "_circle" "3196.794,858.7" "0.075")
(command "_circle" "3196.419,858.7" "0.15")
(command "_circle" "3197.919,860.7" "0.075")
(command "_circle" "3197.544,860.7" "0.075")
(command "_circle" "3197.169,860.7" "0.075")
(command "_circle" "3196.794,860.7" "0.15")
(command "_circle" "3196.419,860.7" "0.15")
(command "_circle" "3197.919,862.7" "0.075")
(command "_circle" "3197.544,862.7" "0.15")
(command "_circle" "3197.169,862.7" "0.075")
(command "_circle" "3196.794,862.7" "0.15")
(command "_circle" "3196.419,862.7" "0.15")
(command "_circle" "3197.919,864.7" "0.075")
(command "_circle" "3197.544,864.7" "0.075")
(command "_circle" "3197.169,864.7" "0.15")
(command "_circle" "3196.794,864.7" "0.15")
(command "_circle" "3196.419,864.7" "0.15")
(command "_circle" "3197.919,866.7" "0.075")
(command "_circle" "3197.544,866.7" "0.15")
(command "_circle" "3197.169,866.7" "0.15")
(command "_circle" "3196.794,866.7" "0.15")
(command "_circle" "3196.419,866.7" "0.15")
(command "_circle" "3197.919,868.7" "0.075")
(command "_circle" "3197.544,868.7" "0.075")
(command "_circle" "3197.169,868.7" "0.075")
(command "_circle" "3196.794,868.7" "0.075")
(command "_circle" "3196.419,868.7" "0.075")
(command "_circle" "3196.044,868.7" "0.15")
(command "_circle" "3197.919,870.7" "0.075")
(command "_circle" "3197.544,870.7" "0.15")
(command "_circle" "3197.169,870.7" "0.075")
(command "_circle" "3196.794,870.7" "0.075")
(command "_circle" "3196.419,870.7" "0.075")
(command "_circle" "3196.044,870.7" "0.15")
(command "_circle" "3197.919,872.7" "0.075")
(command "_circle" "3197.544,872.7" "0.075")
(command "_circle" "3197.169,872.7" "0.15")
(command "_circle" "3196.794,872.7" "0.075")
(command "_circle" "3196.419,872.7" "0.075")
(command "_circle" "3196.044,872.7" "0.15")
(command "_circle" "3197.919,874.7" "0.075")
(command "_circle" "3197.544,874.7" "0.15")
(command "_circle" "3197.169,874.7" "0.15")
(command "_circle" "3196.794,874.7" "0.075")
(command "_circle" "3196.419,874.7" "0.075")
(command "_circle" "3196.044,874.7" "0.15")
(command "_circle" "3197.919,876.7" "0.075")
(command "_circle" "3197.544,876.7" "0.075")
(command "_circle" "3197.169,876.7" "0.075")
(command "_circle" "3196.794,876.7" "0.15")
(command "_circle" "3196.419,876.7" "0.075")
(command "_circle" "3196.044,876.7" "0.15")
(command "_circle" "3197.919,878.7" "0.075")
(command "_circle" "3197.544,878.7" "0.15")
(command "_circle" "3197.169,878.7" "0.075")
(command "_circle" "3196.794,878.7" "0.15")
(command "_circle" "3196.419,878.7" "0.075")
(command "_circle" "3196.044,878.7" "0.15")
(command "_circle" "3197.919,880.7" "0.075")
(command "_circle" "3197.544,880.7" "0.075")
(command "_circle" "3197.169,880.7" "0.15")
(command "_circle" "3196.794,880.7" "0.15")
(command "_circle" "3196.419,880.7" "0.075")
(command "_circle" "3196.044,880.7" "0.15")
(command "_circle" "3197.919,882.7" "0.075")
(command "_circle" "3197.544,882.7" "0.15")
(command "_circle" "3197.169,882.7" "0.15")
(command "_circle" "3196.794,882.7" "0.15")
(command "_circle" "3196.419,882.7" "0.075")
(command "_circle" "3196.044,882.7" "0.15")
(command "_circle" "3197.919,884.7" "0.075")
(command "_circle" "3197.544,884.7" "0.075")
(command "_circle" "3197.169,884.7" "0.075")
(command "_circle" "3196.794,884.7" "0.075")
(command "_circle" "3196.419,884.7" "0.15")
(command "_circle" "3196.044,884.7" "0.15")
(command "_circle" "3197.919,886.7" "0.075")
(command "_circle" "3197.544,886.7" "0.15")
(command "_circle" "3197.169,886.7" "0.075")
(command "_circle" "3196.794,886.7" "0.075")
(command "_circle" "3196.419,886.7" "0.15")
(command "_circle" "3196.044,886.7" "0.15")
(command "_circle" "3197.919,888.7" "0.075")
(command "_circle" "3197.544,888.7" "0.075")
(command "_circle" "3197.169,888.7" "0.15")
(command "_circle" "3196.794,888.7" "0.075")
(command "_circle" "3196.419,888.7" "0.15")
(command "_circle" "3196.044,888.7" "0.15")
(command "_circle" "3197.919,890.7" "0.075")
(command "_circle" "3197.544,890.7" "0.15")
(command "_circle" "3197.169,890.7" "0.15")
(command "_circle" "3196.794,890.7" "0.075")
(command "_circle" "3196.419,890.7" "0.15")
(command "_circle" "3196.044,890.7" "0.15")
(command "_circle" "3197.919,892.7" "0.075")
(command "_circle" "3197.544,892.7" "0.075")
(command "_circle" "3197.169,892.7" "0.075")
(command "_circle" "3196.794,892.7" "0.15")
(command "_circle" "3196.419,892.7" "0.15")
(command "_circle" "3196.044,892.7" "0.15")
(command "_circle" "3197.919,894.7" "0.075")
(command "_circle" "3197.544,894.7" "0.15")
(command "_circle" "3197.169,894.7" "0.075")
(command "_circle" "3196.794,894.7" "0.15")
(command "_circle" "3196.419,894.7" "0.15")
(command "_circle" "3196.044,894.7" "0.15")
(command "_circle" "3197.919,896.7" "0.075")
(command "_circle" "3197.544,896.7" "0.075")
(command "_circle" "3197.169,896.7" "0.15")
(command "_circle" "3196.794,896.7" "0.15")
(command "_circle" "3196.419,896.7" "0.15")
(command "_circle" "3196.044,896.7" "0.15")
(command "_circle" "3197.919,898.7" "0.075")
(command "_circle" "3197.544,898.7" "0.15")
(command "_circle" "3197.169,898.7" "0.15")
(command "_circle" "3196.794,898.7" "0.15")
(command "_circle" "3196.419,898.7" "0.15")
(command "_circle" "3196.044,898.7" "0.15")
(command "_circle" "3197.919,900.7" "0.075")
(command "_circle" "3197.544,900.7" "0.075")
(command "_circle" "3197.169,900.7" "0.075")
(command "_circle" "3196.794,900.7" "0.075")
(command "_circle" "3196.419,900.7" "0.075")
(command "_circle" "3196.044,900.7" "0.075")
(command "_circle" "3195.669,900.7" "0.15")
(command "_circle" "3197.919,902.7" "0.075")
(command "_circle" "3197.544,902.7" "0.15")
(command "_circle" "3197.169,902.7" "0.075")
(command "_circle" "3196.794,902.7" "0.075")
(command "_circle" "3196.419,902.7" "0.075")
(command "_circle" "3196.044,902.7" "0.075")
(command "_circle" "3195.669,902.7" "0.15")
(command "_circle" "3197.919,904.7" "0.075")
(command "_circle" "3197.544,904.7" "0.075")
(command "_circle" "3197.169,904.7" "0.15")
(command "_circle" "3196.794,904.7" "0.075")
(command "_circle" "3196.419,904.7" "0.075")
(command "_circle" "3196.044,904.7" "0.075")
(command "_circle" "3195.669,904.7" "0.15")
(command "_circle" "3197.919,906.7" "0.075")
(command "_circle" "3197.544,906.7" "0.15")
(command "_circle" "3197.169,906.7" "0.15")
(command "_circle" "3196.794,906.7" "0.075")
(command "_circle" "3196.419,906.7" "0.075")
(command "_circle" "3196.044,906.7" "0.075")
(command "_circle" "3195.669,906.7" "0.15")
(command "_circle" "3197.919,908.7" "0.075")
(command "_circle" "3197.544,908.7" "0.075")
(command "_circle" "3197.169,908.7" "0.075")
(command "_circle" "3196.794,908.7" "0.15")
(command "_circle" "3196.419,908.7" "0.075")
(command "_circle" "3196.044,908.7" "0.075")
(command "_circle" "3195.669,908.7" "0.15")
(command "_circle" "3197.919,910.7" "0.075")
(command "_circle" "3197.544,910.7" "0.15")
(command "_circle" "3197.169,910.7" "0.075")
(command "_circle" "3196.794,910.7" "0.15")
(command "_circle" "3196.419,910.7" "0.075")
(command "_circle" "3196.044,910.7" "0.075")
(command "_circle" "3195.669,910.7" "0.15")
(command "_circle" "3197.919,912.7" "0.075")
(command "_circle" "3197.544,912.7" "0.075")
(command "_circle" "3197.169,912.7" "0.15")
(command "_circle" "3196.794,912.7" "0.15")
(command "_circle" "3196.419,912.7" "0.075")
(command "_circle" "3196.044,912.7" "0.075")
(command "_circle" "3195.669,912.7" "0.15")
(command "_circle" "3197.919,914.7" "0.075")
(command "_circle" "3197.544,914.7" "0.15")
(command "_circle" "3197.169,914.7" "0.15")
(command "_circle" "3196.794,914.7" "0.15")
(command "_circle" "3196.419,914.7" "0.075")
(command "_circle" "3196.044,914.7" "0.075")
(command "_circle" "3195.669,914.7" "0.15")
(command "_circle" "3197.919,916.7" "0.075")
(command "_circle" "3197.544,916.7" "0.075")
(command "_circle" "3197.169,916.7" "0.075")
(command "_circle" "3196.794,916.7" "0.075")
(command "_circle" "3196.419,916.7" "0.15")
(command "_circle" "3196.044,916.7" "0.075")
(command "_circle" "3195.669,916.7" "0.15")
(command "_circle" "3197.919,918.7" "0.075")
(command "_circle" "3197.544,918.7" "0.15")
(command "_circle" "3197.169,918.7" "0.075")
(command "_circle" "3196.794,918.7" "0.075")
(command "_circle" "3196.419,918.7" "0.15")
(command "_circle" "3196.044,918.7" "0.075")
(command "_circle" "3195.669,918.7" "0.15")
(command "_circle" "3197.919,920.7" "0.075")
(command "_circle" "3197.544,920.7" "0.075")
(command "_circle" "3197.169,920.7" "0.15")
(command "_circle" "3196.794,920.7" "0.075")
(command "_circle" "3196.419,920.7" "0.15")
(command "_circle" "3196.044,920.7" "0.075")
(command "_circle" "3195.669,920.7" "0.15")
(command "_circle" "3197.919,922.7" "0.075")
(command "_circle" "3197.544,922.7" "0.15")
(command "_circle" "3197.169,922.7" "0.15")
(command "_circle" "3196.794,922.7" "0.075")
(command "_circle" "3196.419,922.7" "0.15")
(command "_circle" "3196.044,922.7" "0.075")
(command "_circle" "3195.669,922.7" "0.15")
(command "_circle" "3197.919,924.7" "0.075")
(command "_circle" "3197.544,924.7" "0.075")
(command "_circle" "3197.169,924.7" "0.075")
(command "_circle" "3196.794,924.7" "0.15")
(command "_circle" "3196.419,924.7" "0.15")
(command "_circle" "3196.044,924.7" "0.075")
(command "_circle" "3195.669,924.7" "0.15")
(command "_circle" "3197.919,926.7" "0.075")
(command "_circle" "3197.544,926.7" "0.15")
(command "_circle" "3197.169,926.7" "0.075")
(command "_circle" "3196.794,926.7" "0.15")
(command "_circle" "3196.419,926.7" "0.15")
(command "_circle" "3196.044,926.7" "0.075")
(command "_circle" "3195.669,926.7" "0.15")
(command "_circle" "3197.919,928.7" "0.075")
(command "_circle" "3197.544,928.7" "0.075")
(command "_circle" "3197.169,928.7" "0.15")
(command "_circle" "3196.794,928.7" "0.15")
(command "_circle" "3196.419,928.7" "0.15")
(command "_circle" "3196.044,928.7" "0.075")
(command "_circle" "3195.669,928.7" "0.15")
(command "_circle" "3197.919,930.7" "0.075")
(command "_circle" "3197.544,930.7" "0.15")
(command "_circle" "3197.169,930.7" "0.15")
(command "_circle" "3196.794,930.7" "0.15")
(command "_circle" "3196.419,930.7" "0.15")
(command "_circle" "3196.044,930.7" "0.075")
(command "_circle" "3195.669,930.7" "0.15")
(command "_circle" "3197.919,932.7" "0.075")
(command "_circle" "3197.544,932.7" "0.075")
(command "_circle" "3197.169,932.7" "0.075")
(command "_circle" "3196.794,932.7" "0.075")
(command "_circle" "3196.419,932.7" "0.075")
(command "_circle" "3196.044,932.7" "0.15")
(command "_circle" "3195.669,932.7" "0.15")
(command "_circle" "3197.919,934.7" "0.075")
(command "_circle" "3197.544,934.7" "0.15")
(command "_circle" "3197.169,934.7" "0.075")
(command "_circle" "3196.794,934.7" "0.075")
(command "_circle" "3196.419,934.7" "0.075")
(command "_circle" "3196.044,934.7" "0.15")
(command "_circle" "3195.669,934.7" "0.15")
(command "_circle" "3197.919,936.7" "0.075")
(command "_circle" "3197.544,936.7" "0.075")
(command "_circle" "3197.169,936.7" "0.15")
(command "_circle" "3196.794,936.7" "0.075")
(command "_circle" "3196.419,936.7" "0.075")
(command "_circle" "3196.044,936.7" "0.15")
(command "_circle" "3195.669,936.7" "0.15")
(command "_circle" "3197.919,938.7" "0.075")
(command "_circle" "3197.544,938.7" "0.15")
(command "_circle" "3197.169,938.7" "0.15")
(command "_circle" "3196.794,938.7" "0.075")
(command "_circle" "3196.419,938.7" "0.075")
(command "_circle" "3196.044,938.7" "0.15")
(command "_circle" "3195.669,938.7" "0.15")
(command "_circle" "3197.919,940.7" "0.075")
(command "_circle" "3197.544,940.7" "0.075")
(command "_circle" "3197.169,940.7" "0.075")
(command "_circle" "3196.794,940.7" "0.15")
(command "_circle" "3196.419,940.7" "0.075")
(command "_circle" "3196.044,940.7" "0.15")
(command "_circle" "3195.669,940.7" "0.15")
(command "_circle" "3197.919,942.7" "0.075")
(command "_circle" "3197.544,942.7" "0.15")
(command "_circle" "3197.169,942.7" "0.075")
(command "_circle" "3196.794,942.7" "0.15")
(command "_circle" "3196.419,942.7" "0.075")
(command "_circle" "3196.044,942.7" "0.15")
(command "_circle" "3195.669,942.7" "0.15")
(command "_circle" "3197.919,944.7" "0.075")
(command "_circle" "3197.544,944.7" "0.075")
(command "_circle" "3197.169,944.7" "0.15")
(command "_circle" "3196.794,944.7" "0.15")
(command "_circle" "3196.419,944.7" "0.075")
(command "_circle" "3196.044,944.7" "0.15")
(command "_circle" "3195.669,944.7" "0.15")
(command "_circle" "3197.919,946.7" "0.075")
(command "_circle" "3197.544,946.7" "0.15")
(command "_circle" "3197.169,946.7" "0.15")
(command "_circle" "3196.794,946.7" "0.15")
(command "_circle" "3196.419,946.7" "0.075")
(command "_circle" "3196.044,946.7" "0.15")
(command "_circle" "3195.669,946.7" "0.15")
(command "_circle" "3197.919,948.7" "0.075")
(command "_circle" "3197.544,948.7" "0.075")
(command "_circle" "3197.169,948.7" "0.075")
(command "_circle" "3196.794,948.7" "0.075")
(command "_circle" "3196.419,948.7" "0.15")
(command "_circle" "3196.044,948.7" "0.15")
(command "_circle" "3195.669,948.7" "0.15")
(command "_circle" "3197.919,950.7" "0.075")
(command "_circle" "3197.544,950.7" "0.15")
(command "_circle" "3197.169,950.7" "0.075")
(command "_circle" "3196.794,950.7" "0.075")
(command "_circle" "3196.419,950.7" "0.15")
(command "_circle" "3196.044,950.7" "0.15")
(command "_circle" "3195.669,950.7" "0.15")
(command "_circle" "3197.919,952.7" "0.075")
(command "_circle" "3197.544,952.7" "0.075")
(command "_circle" "3197.169,952.7" "0.15")
(command "_circle" "3196.794,952.7" "0.075")
(command "_circle" "3196.419,952.7" "0.15")
(command "_circle" "3196.044,952.7" "0.15")
(command "_circle" "3195.669,952.7" "0.15")
(command "_circle" "3197.919,954.7" "0.075")
(command "_circle" "3197.544,954.7" "0.15")
(command "_circle" "3197.169,954.7" "0.15")
(command "_circle" "3196.794,954.7" "0.075")
(command "_circle" "3196.419,954.7" "0.15")
(command "_circle" "3196.044,954.7" "0.15")
(command "_circle" "3195.669,954.7" "0.15")
(command "_circle" "3197.919,956.7" "0.075")
(command "_circle" "3197.544,956.7" "0.075")
(command "_circle" "3197.169,956.7" "0.075")
(command "_circle" "3196.794,956.7" "0.15")
(command "_circle" "3196.419,956.7" "0.15")
(command "_circle" "3196.044,956.7" "0.15")
(command "_circle" "3195.669,956.7" "0.15")
(command "_circle" "3197.919,958.7" "0.075")
(command "_circle" "3197.544,958.7" "0.15")
(command "_circle" "3197.169,958.7" "0.075")
(command "_circle" "3196.794,958.7" "0.15")
(command "_circle" "3196.419,958.7" "0.15")
(command "_circle" "3196.044,958.7" "0.15")
(command "_circle" "3195.669,958.7" "0.15")
(command "_circle" "3197.919,960.7" "0.075")
(command "_circle" "3197.544,960.7" "0.075")
(command "_circle" "3197.169,960.7" "0.15")
(command "_circle" "3196.794,960.7" "0.15")
(command "_circle" "3196.419,960.7" "0.15")
(command "_circle" "3196.044,960.7" "0.15")
(command "_circle" "3195.669,960.7" "0.15")
(command "_circle" "3197.919,962.7" "0.075")
(command "_circle" "3197.544,962.7" "0.15")
(command "_circle" "3197.169,962.7" "0.15")
(command "_circle" "3196.794,962.7" "0.15")
(command "_circle" "3196.419,962.7" "0.15")
(command "_circle" "3196.044,962.7" "0.15")
(command "_circle" "3195.669,962.7" "0.15")
(command "_layer" "set" "nitride" "")
(command "_layer" "set" "text" "")
(command-s "_text" "3186.869,963.3" "2" "-90" "a = 370 nm" )
(sssetfirst nil (ssget "_L"))
(if (not (numberp (vl-string-search "Mac" (getvar "platform")))) (c:txtexp))
(command "_layer" "set" "nitride" "")
(command "_layer" "set" "text" "")
(command-s "_text" "3183.869,963.3" "2" "-90" "gap = 270 nm" )
(sssetfirst nil (ssget "_L"))
(if (not (numberp (vl-string-search "Mac" (getvar "platform")))) (c:txtexp))
(command "_layer" "set" "nitride" "")
(command "_layer" "set" "text" "")
(command-s "_text" "3180.869,963.3" "2" "-90" "amplitude = 134.5 nm" )
(sssetfirst nil (ssget "_L"))
(if (not (numberp (vl-string-search "Mac" (getvar "platform")))) (c:txtexp))
(command "_layer" "set" "nitride" "")
(command "_layer" "set" "text" "")
(command-s "_text" "3177.869,963.3" "2" "-90" "start width = 280 nm" )
(sssetfirst nil (ssget "_L"))
(if (not (numberp (vl-string-search "Mac" (getvar "platform")))) (c:txtexp))
(command "_layer" "set" "nitride" "")
(command "_layer" "set" "text" "")
(command-s "_text" "3174.869,963.3" "2" "-90" "width = 296 nm" )
(sssetfirst nil (ssget "_L"))
(if (not (numberp (vl-string-search "Mac" (getvar "platform")))) (c:txtexp))
(command "_layer" "set" "nitride" "")
(command "_layer" "set" "text" "")
(command-s "_text" "3171.869,963.3" "2" "-90" "taper: 15" )
(sssetfirst nil (ssget "_L"))
(if (not (numberp (vl-string-search "Mac" (getvar "platform")))) (c:txtexp))
(command "_layer" "set" "nitride" "")
(command "_layer" "set" "text" "")
(command-s "_text" "3168.869,963.3" "2" "-90" "nominal: 150" )
(sssetfirst nil (ssget "_L"))
(if (not (numberp (vl-string-search "Mac" (getvar "platform")))) (c:txtexp))
(command "_layer" "set" "nitride" "")
(command "_layer" "set" "indicators" "")
(setq coords (list 
(list 3120.415 940) 
(list 3120.415 920) 
(list 3100.415 900) 
(list 3120.415 880) 
(list 3120.415 860) 
(list 3120.415 900) 
(list 3120.415 887.0711) 
(list 3107.4861 900) 
(list 3120.415 912.9289) 
(list 3120.415 900)))
(apply 'command (append '("pline") coords '("c")))
(command "._fillet" "radius" "1" "._fillet" "P" (entlast))
(setq coords (list 
(list 3279.585 940) 
(list 3279.585 920) 
(list 3299.585 900) 
(list 3279.585 880) 
(list 3279.585 860) 
(list 3279.585 900) 
(list 3279.585 887.0711) 
(list 3292.5139 900) 
(list 3279.585 912.9289) 
(list 3279.585 900)))
(apply 'command (append '("pline") coords '("c")))
(command "._fillet" "radius" "1" "._fillet" "P" (entlast))
(command "_layer" "set" "holes" "")
(command "_circle" "3118.0629,914.1124" "0.5")
(command "_circle" "3115.7109,911.7603" "0.5")
(command "_circle" "3113.3588,909.4083" "0.5")
(command "_circle" "3111.0067,907.0562" "0.5")
(command "_circle" "3108.6547,904.7041" "0.5")
(command "_circle" "3106.3026,902.3521" "0.5")
(command "_circle" "3103.9505,900" "0.5")
(command "_circle" "3106.3026,897.6479" "0.5")
(command "_circle" "3108.6547,895.2959" "0.5")
(command "_circle" "3111.0067,892.9438" "0.5")
(command "_circle" "3113.3588,890.5917" "0.5")
(command "_circle" "3115.7109,888.2397" "0.5")
(command "_circle" "3118.0629,885.8876" "0.5")
(command "_circle" "3281.9371,914.1124" "0.5")
(command "_circle" "3284.2891,911.7603" "0.5")
(command "_circle" "3286.6412,909.4083" "0.5")
(command "_circle" "3288.9933,907.0562" "0.5")
(command "_circle" "3291.3453,904.7041" "0.5")
(command "_circle" "3293.6974,902.3521" "0.5")
(command "_circle" "3296.0495,900" "0.5")
(command "_circle" "3293.6974,897.6479" "0.5")
(command "_circle" "3291.3453,895.2959" "0.5")
(command "_circle" "3288.9933,892.9438" "0.5")
(command "_circle" "3286.6412,890.5917" "0.5")
(command "_circle" "3284.2891,888.2397" "0.5")
(command "_circle" "3281.9371,885.8876" "0.5")
(command "_layer" "set" "nitride" "")
(command "_block" "blkcoupler10" "3200,900" coupler10 "")
(command "_insert" "blkcoupler10" "3200,900" "1" "1" "0")
(command "_insert" "blkcoupler10" "3200,900" "1" "1" "180")
(command "_block" "blksinglenanobeam10" "3200,900" singlenanobeam10 "")
(command "_insert" "blksinglenanobeam10" "3200,900" "1" "1" "0")
(command "_insert" "blksinglenanobeam10" "3200,900" "1" "1" "180")
(command "_block" "blkanglednodearray10" "3200,900" anglednodearray10 "")
(command "_insert" "blkanglednodearray10" "3200,900" "1" "1" "0")
(command "_insert" "blkanglednodearray10" "3200,900" "1" "1" "180")
(command "_block" "blkcooledsinglenanobeam10" "3200,900" cooledsinglenanobeam10 "")
(command "_insert" "blkcooledsinglenanobeam10" "3200,900" "1" "1" "0")
(command "_insert" "blkcooledsinglenanobeam10" "3200,900" "1" "1" "180")
(command "_block" "blkyjunction10" "3200,900" yjunction10 "")
(command "_insert" "blkyjunction10" "3200,900" "1" "1" "0")
(command "_insert" "blkyjunction10" "3200,900" "1" "1" "180")
; DRAWING BULGING VEE GROOVE
(command "_layer" "set" "vgroove" "")
(setq coords (list 
(list 3125.415 -605) 
(list 3125.415 0) 
(list 3125.415 0) 
(list 3125.415 1800) 
(list 3125.415 1800) 
(list 3125.415 2405) 
(list 3274.585 2405) 
(list 3274.585 1800) 
(list 3274.585 1800) 
(list 3274.585 0) 
(list 3274.585 0) 
(list 3274.585 -605)))
(apply 'command (append '("pline") coords '("c")))
(command "._fillet" "radius" "0" "._fillet" "P" (entlast))
(command "_layer" "set" "window" "")
(command "_rectangle" "3125.415,-1935" "3274.585,-600")
(command "_rectangle" "3125.415,2400" "3274.585,5300")
(command "_layer" "set" "grid" "")
(command "_rectangle" "3126.415,-1934" "3149.9433,-1909.2133")
(command "_array" "last" "" "R" "75" "3" "25.7867" "24.5283")
(command "_rectangle" "3201,-1934" "3224.5283,-1909.2133")
(command "_array" "last" "" "R" "75" "3" "25.7867" "24.5283")
(command "_rectangle" "3126.415,1" "3149.9433,25.7")
(command "_array" "last" "" "R" "70" "3" "25.7" "24.5283")
(command "_rectangle" "3201,1" "3224.5283,25.7")
(command "_array" "last" "" "R" "70" "3" "25.7" "24.5283")
(command "_rectangle" "3126.415,1801" "3149.9433,1825.9185")
(command "_array" "last" "" "R" "135" "3" "25.9185" "24.5283")
(command "_rectangle" "3201,1801" "3224.5283,1825.9185")
(command "_array" "last" "" "R" "135" "3" "25.9185" "24.5283")
(command "_layer" "set" "vgrooveFDA" "")
(command "_rectangle" "3274.585,-2233" "3125.415,-1933")
(command "_layer" "set" "nitride" "")
(command "_layer" "set" "holes" "")
(command "_circle" "3277.085,331.5" "0.5")
(command "_array" "last" "" "R" "379" "1" "3" "2.5")
(command "_circle" "3122.915,331.5" "0.5")
(command "_array" "last" "" "R" "379" "1" "3" "-2.5")
(command "_layer" "set" "nitride" "")
(command "_layer" "set" "window" "")
(command "_layer" "set" "window" "")
(command "_rectangle" "3279.585,0" "3440.415,1800")
(command "._fillet" "radius" "20" "._fillet" "P" (entlast))
(command "_layer" "set" "grid" "")
(command "_rectangle" "3280.585,1" "3302.4179,25.7")
(command "_array" "last" "" "R" "70" "7" "25.7" "22.8329")
(command "_layer" "set" "nitride" "")
; DRAWING REGION LAYER
(command "_layer" "set" "regionLayer10" "")
(command "_rectangle" "3120,-460" "3280,2260")
(command "_layer" "set" "nitride" "")
(setq coupler10 nil)
(setq singlenanobeam10 nil)
(setq anglednodearray10 nil)
(setq cooledsinglenanobeam10 nil)
(setq yjunction10 nil)
; DEVICE #11
(command "_layer" "set" "window" "")
(command "_circle" "3432.915,-415" "5")
(command "_circle" "3432.915,-402.5" "5")
(command "_circle" "3432.915,-390" "5")
(command "_circle" "3432.915,-377.5" "5")
(command "_circle" "3420.415,-415" "5")
(command "_circle" "3420.415,-402.5" "5")
(command "_circle" "3420.415,-390" "5")
(command "_circle" "3420.415,-377.5" "5")
(command "_circle" "3407.915,-415" "5")
(command "_circle" "3407.915,-402.5" "5")
(command "_circle" "3407.915,-390" "5")
(command "_layer" "set" "nitride" "")
(setq currobj nil)
(setq currobj (ssadd))
; DRAWING COUPLER
(setq coords (list 
(list 3520.0645 -415) 
(list 3520.0645 -413) 
(list 3593.585 -413) 
(list 3593.585 -413) 
(list 3593.9677 -413.0761) 
(list 3594.2921 -413.2929) 
(list 3594.5089 -413.6173) 
(list 3594.585 -414) 
(list 3594.585 -411.8) 
(list 3594.585 -411.8) 
(list 3594.5089 -412.1827) 
(list 3594.2921 -412.5071) 
(list 3593.9677 -412.7239) 
(list 3593.585 -412.8) 
(list 3520.0645 -412.8) 
(list 3520.0645 -410.8) 
(list 3519.9355 -410.8) 
(list 3519.9355 -412.8) 
(list 3446.415 -412.8) 
(list 3446.0323 -412.7239) 
(list 3445.7079 -412.5071) 
(list 3445.4911 -412.1827) 
(list 3445.415 -411.8) 
(list 3445.415 -411.8) 
(list 3445.415 -414) 
(list 3445.4911 -413.6173) 
(list 3445.7079 -413.2929) 
(list 3446.0323 -413.0761) 
(list 3446.415 -413) 
(list 3446.415 -413) 
(list 3519.9355 -413) 
(list 3519.9355 -415)))
(apply 'command (append '("pline") coords '("c")))
(setq currobj (ssadd (entlast) currobj))
(command "._fillet" "radius" "0.3" "._fillet" "P" (entlast))
(command "_layer" "set" "holes" "")
(command "_circle" "3520,-412.9" "0.113")
(setq currobj (ssadd (entlast) currobj))
(command "_layer" "set" "nitride" "")
(command "_layer" "set" "text" "")
(command "_circle" "3519.2,-415" "0.075")
(command "_circle" "3519.2,-414.7" "0.075")
(command "_circle" "3519.2,-414.4" "0.075")
(command "_circle" "3518.9,-415" "0.075")
(command "_circle" "3518.9,-414.7" "0.075")
(command "_circle" "3518.9,-414.4" "0.075")
(command "_circle" "3518.6,-415" "0.075")
(command "_circle" "3518.6,-414.7" "0.075")
(command "_circle" "3518.6,-414.4" "0.075")
(command "_layer" "set" "nitride" "")
(command "_layer" "set" "prebias" "")
(command "_rectangle" "3445.415,-414" "3594.585,-411.8")
(setq currobj (ssadd (entlast) currobj))
(command "_rectangle" "3519.9355,-415" "3520.0645,-410.8")
(setq currobj (ssadd (entlast) currobj))
(command "_layer" "set" "nitride" "")
(setq coupler11 currobj)
(setq currobj nil)
(setq currobj (ssadd))
; DRAWING SINGLE NANOBEAM
(setq coords (list 
(list 3520.0645 -410.8) 
(list 3520.0645 -409.1417) 
(list 3520.0645 -407.4833) 
(list 3520.0645 -405.825) 
(list 3520.0645 -404.1667) 
(list 3520.0645 -402.5083) 
(list 3520.0645 -400.85) 
(list 3520.0645 -399.1917) 
(list 3520.0645 -397.5333) 
(list 3520.0646 -395.875) 
(list 3520.0646 -394.2167) 
(list 3520.0646 -392.5583) 
(list 3520.0646 -390.9) 
(list 3520.0647 -389.2417) 
(list 3520.0647 -387.5833) 
(list 3520.0647 -385.925) 
(list 3520.0648 -384.2667) 
(list 3520.0648 -382.6083) 
(list 3520.0649 -380.95) 
(list 3520.065 -379.2917) 
(list 3520.0651 -377.6333) 
(list 3520.0651 -375.975) 
(list 3520.0652 -374.3167) 
(list 3520.0653 -372.6583) 
(list 3520.0655 -371) 
(list 3520.0656 -369.3417) 
(list 3520.0657 -367.6833) 
(list 3520.0659 -366.025) 
(list 3520.066 -364.3667) 
(list 3520.0662 -362.7083) 
(list 3520.0664 -361.05) 
(list 3520.0666 -359.3917) 
(list 3520.0668 -357.7333) 
(list 3520.067 -356.075) 
(list 3520.0672 -354.4167) 
(list 3520.0675 -352.7583) 
(list 3520.0678 -351.1) 
(list 3520.068 -349.4417) 
(list 3520.0683 -347.7833) 
(list 3520.0686 -346.125) 
(list 3520.069 -344.4667) 
(list 3520.0693 -342.8083) 
(list 3520.0697 -341.15) 
(list 3520.07 -339.4917) 
(list 3520.0704 -337.8333) 
(list 3520.0709 -336.175) 
(list 3520.0713 -334.5167) 
(list 3520.0717 -332.8583) 
(list 3520.0722 -331.2) 
(list 3520.0727 -329.5417) 
(list 3520.0732 -327.8833) 
(list 3520.0738 -326.225) 
(list 3520.0743 -324.5667) 
(list 3520.0749 -322.9083) 
(list 3520.0755 -321.25) 
(list 3520.0761 -319.5917) 
(list 3520.0767 -317.9333) 
(list 3520.0774 -316.275) 
(list 3520.0781 -314.6167) 
(list 3520.0788 -312.9583) 
(list 3520.0796 -311.3) 
(list 3520.0803 -309.6417) 
(list 3520.0811 -307.9833) 
(list 3520.0819 -306.325) 
(list 3520.0828 -304.6667) 
(list 3520.0837 -303.0083) 
(list 3520.0845 -301.35) 
(list 3520.0855 -299.6917) 
(list 3520.0864 -298.0333) 
(list 3520.0874 -296.375) 
(list 3520.0884 -294.7167) 
(list 3520.0895 -293.0583) 
(list 3520.0905 -291.4) 
(list 3520.0916 -289.7417) 
(list 3520.0928 -288.0833) 
(list 3520.0939 -286.425) 
(list 3520.0951 -284.7667) 
(list 3520.0963 -283.1083) 
(list 3520.0976 -281.45) 
(list 3520.0989 -279.7917) 
(list 3520.1002 -278.1333) 
(list 3520.1016 -276.475) 
(list 3520.1029 -274.8167) 
(list 3520.1044 -273.1583) 
(list 3520.1058 -271.5) 
(list 3520.1073 -269.8417) 
(list 3520.1089 -268.1833) 
(list 3520.1104 -266.525) 
(list 3520.112 -264.8667) 
(list 3520.1137 -263.2083) 
(list 3520.1153 -261.55) 
(list 3520.117 -259.8917) 
(list 3520.1188 -258.2333) 
(list 3520.1206 -256.575) 
(list 3520.1224 -254.9167) 
(list 3520.1243 -253.2583) 
(list 3520.1262 -251.6) 
(list 3520.1281 -249.9417) 
(list 3520.1301 -248.2833) 
(list 3520.1322 -246.625) 
(list 3520.1342 -244.9667) 
(list 3520.1363 -243.3083) 
(list 3520.1385 -241.65) 
(list 3520.1407 -239.9917) 
(list 3520.1429 -238.3333) 
(list 3520.1452 -236.675) 
(list 3520.1476 -235.0167) 
(list 3520.1499 -233.3583) 
(list 3520.1523 -231.7) 
(list 3520.1548 -230.0417) 
(list 3520.1573 -228.3833) 
(list 3520.1599 -226.725) 
(list 3520.1625 -225.0667) 
(list 3520.1651 -223.4083) 
(list 3520.1678 -221.75) 
(list 3520.1706 -220.0917) 
(list 3520.1733 -218.4333) 
(list 3520.1762 -216.775) 
(list 3520.1791 -215.1167) 
(list 3520.182 -213.4583) 
(list 3520.185 -211.8) 
(list 3519.815 -211.8) 
(list 3519.818 -213.4583) 
(list 3519.8209 -215.1167) 
(list 3519.8238 -216.775) 
(list 3519.8267 -218.4333) 
(list 3519.8294 -220.0917) 
(list 3519.8322 -221.75) 
(list 3519.8349 -223.4083) 
(list 3519.8375 -225.0667) 
(list 3519.8401 -226.725) 
(list 3519.8427 -228.3833) 
(list 3519.8452 -230.0417) 
(list 3519.8477 -231.7) 
(list 3519.8501 -233.3583) 
(list 3519.8524 -235.0167) 
(list 3519.8548 -236.675) 
(list 3519.8571 -238.3333) 
(list 3519.8593 -239.9917) 
(list 3519.8615 -241.65) 
(list 3519.8637 -243.3083) 
(list 3519.8658 -244.9667) 
(list 3519.8678 -246.625) 
(list 3519.8699 -248.2833) 
(list 3519.8719 -249.9417) 
(list 3519.8738 -251.6) 
(list 3519.8757 -253.2583) 
(list 3519.8776 -254.9167) 
(list 3519.8794 -256.575) 
(list 3519.8812 -258.2333) 
(list 3519.883 -259.8917) 
(list 3519.8847 -261.55) 
(list 3519.8863 -263.2083) 
(list 3519.888 -264.8667) 
(list 3519.8896 -266.525) 
(list 3519.8911 -268.1833) 
(list 3519.8927 -269.8417) 
(list 3519.8942 -271.5) 
(list 3519.8956 -273.1583) 
(list 3519.8971 -274.8167) 
(list 3519.8984 -276.475) 
(list 3519.8998 -278.1333) 
(list 3519.9011 -279.7917) 
(list 3519.9024 -281.45) 
(list 3519.9037 -283.1083) 
(list 3519.9049 -284.7667) 
(list 3519.9061 -286.425) 
(list 3519.9072 -288.0833) 
(list 3519.9084 -289.7417) 
(list 3519.9095 -291.4) 
(list 3519.9105 -293.0583) 
(list 3519.9116 -294.7167) 
(list 3519.9126 -296.375) 
(list 3519.9136 -298.0333) 
(list 3519.9145 -299.6917) 
(list 3519.9155 -301.35) 
(list 3519.9163 -303.0083) 
(list 3519.9172 -304.6667) 
(list 3519.9181 -306.325) 
(list 3519.9189 -307.9833) 
(list 3519.9197 -309.6417) 
(list 3519.9204 -311.3) 
(list 3519.9212 -312.9583) 
(list 3519.9219 -314.6167) 
(list 3519.9226 -316.275) 
(list 3519.9233 -317.9333) 
(list 3519.9239 -319.5917) 
(list 3519.9245 -321.25) 
(list 3519.9251 -322.9083) 
(list 3519.9257 -324.5667) 
(list 3519.9262 -326.225) 
(list 3519.9268 -327.8833) 
(list 3519.9273 -329.5417) 
(list 3519.9278 -331.2) 
(list 3519.9283 -332.8583) 
(list 3519.9287 -334.5167) 
(list 3519.9291 -336.175) 
(list 3519.9296 -337.8333) 
(list 3519.93 -339.4917) 
(list 3519.9303 -341.15) 
(list 3519.9307 -342.8083) 
(list 3519.931 -344.4667) 
(list 3519.9314 -346.125) 
(list 3519.9317 -347.7833) 
(list 3519.932 -349.4417) 
(list 3519.9322 -351.1) 
(list 3519.9325 -352.7583) 
(list 3519.9328 -354.4167) 
(list 3519.933 -356.075) 
(list 3519.9332 -357.7333) 
(list 3519.9334 -359.3917) 
(list 3519.9336 -361.05) 
(list 3519.9338 -362.7083) 
(list 3519.934 -364.3667) 
(list 3519.9341 -366.025) 
(list 3519.9343 -367.6833) 
(list 3519.9344 -369.3417) 
(list 3519.9345 -371) 
(list 3519.9347 -372.6583) 
(list 3519.9348 -374.3167) 
(list 3519.9349 -375.975) 
(list 3519.9349 -377.6333) 
(list 3519.935 -379.2917) 
(list 3519.9351 -380.95) 
(list 3519.9352 -382.6083) 
(list 3519.9352 -384.2667) 
(list 3519.9353 -385.925) 
(list 3519.9353 -387.5833) 
(list 3519.9353 -389.2417) 
(list 3519.9354 -390.9) 
(list 3519.9354 -392.5583) 
(list 3519.9354 -394.2167) 
(list 3519.9354 -395.875) 
(list 3519.9355 -397.5333) 
(list 3519.9355 -399.1917) 
(list 3519.9355 -400.85) 
(list 3519.9355 -402.5083) 
(list 3519.9355 -404.1667) 
(list 3519.9355 -405.825) 
(list 3519.9355 -407.4833) 
(list 3519.9355 -409.1417) 
(list 3519.9355 -410.8)))
(apply 'command (append '("pline") coords '("c")))
(setq currobj (ssadd (entlast) currobj))
(command "_layer" "set" "prebias" "")
(command "_rectangle" "3519.815,-410.8" "3520.185,-211.8")
(setq currobj (ssadd (entlast) currobj))
(command "_layer" "set" "nitride" "")
(setq singlenanobeam11 currobj)
(setq currobj nil)
(setq currobj (ssadd))
; DRAWING NODE ARRAY
(setq coords (list 
(list 3520.185 -211.8) 
(list 3520.5625 -201.8) 
(list 3520.5625 -201.8) 
(list 3520.5625 -200.8) 
(list 3594.585 -212.6864) 
(list 3594.585 -207.7434) 
(list 3520.5625 -197.357) 
(list 3520.5625 -196.357) 
(list 3520.5625 -196.357) 
(list 3520.2625 -186.357) 
(list 3519.7375 -186.357) 
(list 3519.4375 -196.357) 
(list 3519.4375 -196.357) 
(list 3519.4375 -197.357) 
(list 3445.415 -207.7434) 
(list 3445.415 -212.6864) 
(list 3519.4375 -200.8) 
(list 3519.4375 -201.8) 
(list 3519.4375 -201.8) 
(list 3519.815 -211.8)))
(apply 'command (append '("pline") coords '("c")))
(setq currobj (ssadd (entlast) currobj))
(command "_layer" "set" "prebias" "")
(setq coords (list 
(list 3519.4375 -212.6864) 
(list 3519.4375 -200.8) 
(list 3445.415 -212.6864) 
(list 3445.415 -207.7434) 
(list 3519.4375 -197.357) 
(list 3519.4375 -186.357) 
(list 3520.5625 -186.357) 
(list 3520.5625 -197.357) 
(list 3594.585 -207.7434) 
(list 3594.585 -212.6864) 
(list 3520.5625 -200.8) 
(list 3520.5625 -212.6864)))
(apply 'command (append '("pline") coords '("c")))
(setq currobj (ssadd (entlast) currobj))
(command "_layer" "set" "nitride" "")
(command "_layer" "set" "fda1" "")
(setq coords (list 
(list 3520.5625 -200.657) 
(list 3594.585 -212.5434) 
(list 3594.585 -212.3664) 
(list 3520.5625 -200.58)))
(apply 'command (append '("pline") coords '("c")))
(setq currobj (ssadd (entlast) currobj))
(setq coords (list 
(list 3520.5625 -200.437) 
(list 3594.585 -212.2234) 
(list 3594.585 -212.0464) 
(list 3520.5625 -200.36)))
(apply 'command (append '("pline") coords '("c")))
(setq currobj (ssadd (entlast) currobj))
(setq coords (list 
(list 3520.5625 -200.217) 
(list 3594.585 -211.9034) 
(list 3594.585 -211.7264) 
(list 3520.5625 -200.14)))
(apply 'command (append '("pline") coords '("c")))
(setq currobj (ssadd (entlast) currobj))
(setq coords (list 
(list 3520.5625 -199.997) 
(list 3594.585 -211.5834) 
(list 3594.585 -211.4064) 
(list 3520.5625 -199.92)))
(apply 'command (append '("pline") coords '("c")))
(setq currobj (ssadd (entlast) currobj))
(setq coords (list 
(list 3520.5625 -199.777) 
(list 3594.585 -211.2634) 
(list 3594.585 -211.0864) 
(list 3520.5625 -199.7)))
(apply 'command (append '("pline") coords '("c")))
(setq currobj (ssadd (entlast) currobj))
(setq coords (list 
(list 3520.5625 -199.557) 
(list 3594.585 -210.9434) 
(list 3594.585 -210.7664) 
(list 3520.5625 -199.48)))
(apply 'command (append '("pline") coords '("c")))
(setq currobj (ssadd (entlast) currobj))
(setq coords (list 
(list 3520.5625 -199.337) 
(list 3594.585 -210.6234) 
(list 3594.585 -210.4464) 
(list 3520.5625 -199.26)))
(apply 'command (append '("pline") coords '("c")))
(setq currobj (ssadd (entlast) currobj))
(setq coords (list 
(list 3520.5625 -199.117) 
(list 3594.585 -210.3034) 
(list 3594.585 -210.1264) 
(list 3520.5625 -199.04)))
(apply 'command (append '("pline") coords '("c")))
(setq currobj (ssadd (entlast) currobj))
(setq coords (list 
(list 3520.5625 -198.897) 
(list 3594.585 -209.9834) 
(list 3594.585 -209.8064) 
(list 3520.5625 -198.82)))
(apply 'command (append '("pline") coords '("c")))
(setq currobj (ssadd (entlast) currobj))
(setq coords (list 
(list 3520.5625 -198.677) 
(list 3594.585 -209.6634) 
(list 3594.585 -209.4864) 
(list 3520.5625 -198.6)))
(apply 'command (append '("pline") coords '("c")))
(setq currobj (ssadd (entlast) currobj))
(setq coords (list 
(list 3520.5625 -198.457) 
(list 3594.585 -209.3434) 
(list 3594.585 -209.1664) 
(list 3520.5625 -198.38)))
(apply 'command (append '("pline") coords '("c")))
(setq currobj (ssadd (entlast) currobj))
(setq coords (list 
(list 3520.5625 -198.237) 
(list 3594.585 -209.0234) 
(list 3594.585 -208.8464) 
(list 3520.5625 -198.16)))
(apply 'command (append '("pline") coords '("c")))
(setq currobj (ssadd (entlast) currobj))
(setq coords (list 
(list 3520.5625 -198.017) 
(list 3594.585 -208.7034) 
(list 3594.585 -208.5264) 
(list 3520.5625 -197.94)))
(apply 'command (append '("pline") coords '("c")))
(setq currobj (ssadd (entlast) currobj))
(setq coords (list 
(list 3520.5625 -197.797) 
(list 3594.585 -208.3834) 
(list 3594.585 -208.2064) 
(list 3520.5625 -197.72)))
(apply 'command (append '("pline") coords '("c")))
(setq currobj (ssadd (entlast) currobj))
(setq coords (list 
(list 3520.5625 -197.577) 
(list 3594.585 -208.0634) 
(list 3594.585 -207.8864) 
(list 3520.5625 -197.5)))
(apply 'command (append '("pline") coords '("c")))
(setq currobj (ssadd (entlast) currobj))
(setq coords (list 
(list 3519.4375 -197.5) 
(list 3445.415 -207.8864) 
(list 3445.415 -208.0634) 
(list 3519.4375 -197.577)))
(apply 'command (append '("pline") coords '("c")))
(setq currobj (ssadd (entlast) currobj))
(setq coords (list 
(list 3519.4375 -197.72) 
(list 3445.415 -208.2064) 
(list 3445.415 -208.3834) 
(list 3519.4375 -197.797)))
(apply 'command (append '("pline") coords '("c")))
(setq currobj (ssadd (entlast) currobj))
(setq coords (list 
(list 3519.4375 -197.94) 
(list 3445.415 -208.5264) 
(list 3445.415 -208.7034) 
(list 3519.4375 -198.017)))
(apply 'command (append '("pline") coords '("c")))
(setq currobj (ssadd (entlast) currobj))
(setq coords (list 
(list 3519.4375 -198.16) 
(list 3445.415 -208.8464) 
(list 3445.415 -209.0234) 
(list 3519.4375 -198.237)))
(apply 'command (append '("pline") coords '("c")))
(setq currobj (ssadd (entlast) currobj))
(setq coords (list 
(list 3519.4375 -198.38) 
(list 3445.415 -209.1664) 
(list 3445.415 -209.3434) 
(list 3519.4375 -198.457)))
(apply 'command (append '("pline") coords '("c")))
(setq currobj (ssadd (entlast) currobj))
(setq coords (list 
(list 3519.4375 -198.6) 
(list 3445.415 -209.4864) 
(list 3445.415 -209.6634) 
(list 3519.4375 -198.677)))
(apply 'command (append '("pline") coords '("c")))
(setq currobj (ssadd (entlast) currobj))
(setq coords (list 
(list 3519.4375 -198.82) 
(list 3445.415 -209.8064) 
(list 3445.415 -209.9834) 
(list 3519.4375 -198.897)))
(apply 'command (append '("pline") coords '("c")))
(setq currobj (ssadd (entlast) currobj))
(setq coords (list 
(list 3519.4375 -199.04) 
(list 3445.415 -210.1264) 
(list 3445.415 -210.3034) 
(list 3519.4375 -199.117)))
(apply 'command (append '("pline") coords '("c")))
(setq currobj (ssadd (entlast) currobj))
(setq coords (list 
(list 3519.4375 -199.26) 
(list 3445.415 -210.4464) 
(list 3445.415 -210.6234) 
(list 3519.4375 -199.337)))
(apply 'command (append '("pline") coords '("c")))
(setq currobj (ssadd (entlast) currobj))
(setq coords (list 
(list 3519.4375 -199.48) 
(list 3445.415 -210.7664) 
(list 3445.415 -210.9434) 
(list 3519.4375 -199.557)))
(apply 'command (append '("pline") coords '("c")))
(setq currobj (ssadd (entlast) currobj))
(setq coords (list 
(list 3519.4375 -199.7) 
(list 3445.415 -211.0864) 
(list 3445.415 -211.2634) 
(list 3519.4375 -199.777)))
(apply 'command (append '("pline") coords '("c")))
(setq currobj (ssadd (entlast) currobj))
(setq coords (list 
(list 3519.4375 -199.92) 
(list 3445.415 -211.4064) 
(list 3445.415 -211.5834) 
(list 3519.4375 -199.997)))
(apply 'command (append '("pline") coords '("c")))
(setq currobj (ssadd (entlast) currobj))
(setq coords (list 
(list 3519.4375 -200.14) 
(list 3445.415 -211.7264) 
(list 3445.415 -211.9034) 
(list 3519.4375 -200.217)))
(apply 'command (append '("pline") coords '("c")))
(setq currobj (ssadd (entlast) currobj))
(setq coords (list 
(list 3519.4375 -200.36) 
(list 3445.415 -212.0464) 
(list 3445.415 -212.2234) 
(list 3519.4375 -200.437)))
(apply 'command (append '("pline") coords '("c")))
(setq currobj (ssadd (entlast) currobj))
(setq coords (list 
(list 3519.4375 -200.58) 
(list 3445.415 -212.3664) 
(list 3445.415 -212.5434) 
(list 3519.4375 -200.657)))
(apply 'command (append '("pline") coords '("c")))
(setq currobj (ssadd (entlast) currobj))
(command "_layer" "set" "nitride" "")
(command "_layer" "set" "text" "")
(command "_circle" "3518.985,-211.8" "0.075")
(command "_circle" "3518.985,-211.5" "0.075")
(command "_circle" "3518.985,-211.2" "0.075")
(command "_circle" "3518.985,-210.9" "0.075")
(command "_circle" "3518.985,-210.6" "0.075")
(command "_circle" "3518.685,-211.8" "0.075")
(command "_circle" "3518.685,-211.5" "0.075")
(command "_circle" "3518.685,-211.2" "0.075")
(command "_circle" "3518.685,-210.9" "0.075")
(command "_circle" "3518.685,-210.6" "0.075")
(command "_circle" "3518.385,-211.8" "0.075")
(command "_circle" "3518.385,-211.5" "0.075")
(command "_circle" "3518.385,-211.2" "0.075")
(command "_circle" "3518.385,-210.9" "0.075")
(command "_circle" "3518.385,-210.6" "0.075")
(command "_circle" "3518.085,-211.8" "0.075")
(command "_circle" "3518.085,-211.5" "0.075")
(command "_circle" "3518.085,-211.2" "0.075")
(command "_circle" "3518.085,-210.9" "0.075")
(command "_circle" "3518.085,-210.6" "0.075")
(command "_circle" "3517.785,-211.8" "0.075")
(command "_circle" "3517.785,-211.5" "0.075")
(command "_circle" "3517.785,-211.2" "0.075")
(command "_circle" "3517.785,-210.9" "0.075")
(command "_circle" "3517.785,-210.6" "0.075")
(command "_layer" "set" "nitride" "")
(setq anglednodearray11 currobj)
(setq currobj nil)
(setq currobj (ssadd))
; DRAWING COOLED SINGLE NANOBEAM
(setq coords (list 
(list 3520.2625 -186.357) 
(list 3520.2625 -181.357) 
(list 3519.7375 -181.357) 
(list 3519.7375 -186.357)))
(apply 'command (append '("pline") coords '("c")))
(setq currobj (ssadd (entlast) currobj))
(command "_layer" "set" "prebias" "")
(command "_rectangle" "3519.7375,-186.357" "3520.2625,-181.357")
(setq currobj (ssadd (entlast) currobj))
(command "_layer" "set" "nitride" "")
(setq coords (list 
(list 3520.2625 -181.357) 
(list 3520.5625 -171.357) 
(list 3520.5625 -171.357) 
(list 3520.5625 -170.357) 
(list 3594.585 -171.107) 
(list 3594.585 -166.164) 
(list 3520.5625 -166.914) 
(list 3520.5625 -165.914) 
(list 3520.5625 -165.914) 
(list 3520.2625 -155.914) 
(list 3519.7375 -155.914) 
(list 3519.4375 -165.914) 
(list 3519.4375 -165.914) 
(list 3519.4375 -166.914) 
(list 3445.415 -166.164) 
(list 3445.415 -171.107) 
(list 3519.4375 -170.357) 
(list 3519.4375 -171.357) 
(list 3519.4375 -171.357) 
(list 3519.7375 -181.357)))
(apply 'command (append '("pline") coords '("c")))
(setq currobj (ssadd (entlast) currobj))
(command "_layer" "set" "prebias" "")
(setq coords (list 
(list 3519.4375 -181.357) 
(list 3519.4375 -170.357) 
(list 3445.415 -171.107) 
(list 3445.415 -166.164) 
(list 3519.4375 -166.914) 
(list 3519.4375 -155.914) 
(list 3520.5625 -155.914) 
(list 3520.5625 -166.914) 
(list 3594.585 -166.164) 
(list 3594.585 -171.107) 
(list 3520.5625 -170.357) 
(list 3520.5625 -181.357)))
(apply 'command (append '("pline") coords '("c")))
(setq currobj (ssadd (entlast) currobj))
(command "_layer" "set" "nitride" "")
(command "_layer" "set" "fda1" "")
(setq coords (list 
(list 3520.5625 -170.214) 
(list 3594.585 -170.964) 
(list 3594.585 -170.787) 
(list 3520.5625 -170.137)))
(apply 'command (append '("pline") coords '("c")))
(setq currobj (ssadd (entlast) currobj))
(setq coords (list 
(list 3520.5625 -169.994) 
(list 3594.585 -170.644) 
(list 3594.585 -170.467) 
(list 3520.5625 -169.917)))
(apply 'command (append '("pline") coords '("c")))
(setq currobj (ssadd (entlast) currobj))
(setq coords (list 
(list 3520.5625 -169.774) 
(list 3594.585 -170.324) 
(list 3594.585 -170.147) 
(list 3520.5625 -169.697)))
(apply 'command (append '("pline") coords '("c")))
(setq currobj (ssadd (entlast) currobj))
(setq coords (list 
(list 3520.5625 -169.554) 
(list 3594.585 -170.004) 
(list 3594.585 -169.827) 
(list 3520.5625 -169.477)))
(apply 'command (append '("pline") coords '("c")))
(setq currobj (ssadd (entlast) currobj))
(setq coords (list 
(list 3520.5625 -169.334) 
(list 3594.585 -169.684) 
(list 3594.585 -169.507) 
(list 3520.5625 -169.257)))
(apply 'command (append '("pline") coords '("c")))
(setq currobj (ssadd (entlast) currobj))
(setq coords (list 
(list 3520.5625 -169.114) 
(list 3594.585 -169.364) 
(list 3594.585 -169.187) 
(list 3520.5625 -169.037)))
(apply 'command (append '("pline") coords '("c")))
(setq currobj (ssadd (entlast) currobj))
(setq coords (list 
(list 3520.5625 -168.894) 
(list 3594.585 -169.044) 
(list 3594.585 -168.867) 
(list 3520.5625 -168.817)))
(apply 'command (append '("pline") coords '("c")))
(setq currobj (ssadd (entlast) currobj))
(setq coords (list 
(list 3520.5625 -168.674) 
(list 3594.585 -168.724) 
(list 3594.585 -168.547) 
(list 3520.5625 -168.597)))
(apply 'command (append '("pline") coords '("c")))
(setq currobj (ssadd (entlast) currobj))
(setq coords (list 
(list 3520.5625 -168.454) 
(list 3594.585 -168.404) 
(list 3594.585 -168.227) 
(list 3520.5625 -168.377)))
(apply 'command (append '("pline") coords '("c")))
(setq currobj (ssadd (entlast) currobj))
(setq coords (list 
(list 3520.5625 -168.234) 
(list 3594.585 -168.084) 
(list 3594.585 -167.907) 
(list 3520.5625 -168.157)))
(apply 'command (append '("pline") coords '("c")))
(setq currobj (ssadd (entlast) currobj))
(setq coords (list 
(list 3520.5625 -168.014) 
(list 3594.585 -167.764) 
(list 3594.585 -167.587) 
(list 3520.5625 -167.937)))
(apply 'command (append '("pline") coords '("c")))
(setq currobj (ssadd (entlast) currobj))
(setq coords (list 
(list 3520.5625 -167.794) 
(list 3594.585 -167.444) 
(list 3594.585 -167.267) 
(list 3520.5625 -167.717)))
(apply 'command (append '("pline") coords '("c")))
(setq currobj (ssadd (entlast) currobj))
(setq coords (list 
(list 3520.5625 -167.574) 
(list 3594.585 -167.124) 
(list 3594.585 -166.947) 
(list 3520.5625 -167.497)))
(apply 'command (append '("pline") coords '("c")))
(setq currobj (ssadd (entlast) currobj))
(setq coords (list 
(list 3520.5625 -167.354) 
(list 3594.585 -166.804) 
(list 3594.585 -166.627) 
(list 3520.5625 -167.277)))
(apply 'command (append '("pline") coords '("c")))
(setq currobj (ssadd (entlast) currobj))
(setq coords (list 
(list 3520.5625 -167.134) 
(list 3594.585 -166.484) 
(list 3594.585 -166.307) 
(list 3520.5625 -167.057)))
(apply 'command (append '("pline") coords '("c")))
(setq currobj (ssadd (entlast) currobj))
(setq coords (list 
(list 3519.4375 -167.057) 
(list 3445.415 -166.307) 
(list 3445.415 -166.484) 
(list 3519.4375 -167.134)))
(apply 'command (append '("pline") coords '("c")))
(setq currobj (ssadd (entlast) currobj))
(setq coords (list 
(list 3519.4375 -167.277) 
(list 3445.415 -166.627) 
(list 3445.415 -166.804) 
(list 3519.4375 -167.354)))
(apply 'command (append '("pline") coords '("c")))
(setq currobj (ssadd (entlast) currobj))
(setq coords (list 
(list 3519.4375 -167.497) 
(list 3445.415 -166.947) 
(list 3445.415 -167.124) 
(list 3519.4375 -167.574)))
(apply 'command (append '("pline") coords '("c")))
(setq currobj (ssadd (entlast) currobj))
(setq coords (list 
(list 3519.4375 -167.717) 
(list 3445.415 -167.267) 
(list 3445.415 -167.444) 
(list 3519.4375 -167.794)))
(apply 'command (append '("pline") coords '("c")))
(setq currobj (ssadd (entlast) currobj))
(setq coords (list 
(list 3519.4375 -167.937) 
(list 3445.415 -167.587) 
(list 3445.415 -167.764) 
(list 3519.4375 -168.014)))
(apply 'command (append '("pline") coords '("c")))
(setq currobj (ssadd (entlast) currobj))
(setq coords (list 
(list 3519.4375 -168.157) 
(list 3445.415 -167.907) 
(list 3445.415 -168.084) 
(list 3519.4375 -168.234)))
(apply 'command (append '("pline") coords '("c")))
(setq currobj (ssadd (entlast) currobj))
(setq coords (list 
(list 3519.4375 -168.377) 
(list 3445.415 -168.227) 
(list 3445.415 -168.404) 
(list 3519.4375 -168.454)))
(apply 'command (append '("pline") coords '("c")))
(setq currobj (ssadd (entlast) currobj))
(setq coords (list 
(list 3519.4375 -168.597) 
(list 3445.415 -168.547) 
(list 3445.415 -168.724) 
(list 3519.4375 -168.674)))
(apply 'command (append '("pline") coords '("c")))
(setq currobj (ssadd (entlast) currobj))
(setq coords (list 
(list 3519.4375 -168.817) 
(list 3445.415 -168.867) 
(list 3445.415 -169.044) 
(list 3519.4375 -168.894)))
(apply 'command (append '("pline") coords '("c")))
(setq currobj (ssadd (entlast) currobj))
(setq coords (list 
(list 3519.4375 -169.037) 
(list 3445.415 -169.187) 
(list 3445.415 -169.364) 
(list 3519.4375 -169.114)))
(apply 'command (append '("pline") coords '("c")))
(setq currobj (ssadd (entlast) currobj))
(setq coords (list 
(list 3519.4375 -169.257) 
(list 3445.415 -169.507) 
(list 3445.415 -169.684) 
(list 3519.4375 -169.334)))
(apply 'command (append '("pline") coords '("c")))
(setq currobj (ssadd (entlast) currobj))
(setq coords (list 
(list 3519.4375 -169.477) 
(list 3445.415 -169.827) 
(list 3445.415 -170.004) 
(list 3519.4375 -169.554)))
(apply 'command (append '("pline") coords '("c")))
(setq currobj (ssadd (entlast) currobj))
(setq coords (list 
(list 3519.4375 -169.697) 
(list 3445.415 -170.147) 
(list 3445.415 -170.324) 
(list 3519.4375 -169.774)))
(apply 'command (append '("pline") coords '("c")))
(setq currobj (ssadd (entlast) currobj))
(setq coords (list 
(list 3519.4375 -169.917) 
(list 3445.415 -170.467) 
(list 3445.415 -170.644) 
(list 3519.4375 -169.994)))
(apply 'command (append '("pline") coords '("c")))
(setq currobj (ssadd (entlast) currobj))
(setq coords (list 
(list 3519.4375 -170.137) 
(list 3445.415 -170.787) 
(list 3445.415 -170.964) 
(list 3519.4375 -170.214)))
(apply 'command (append '("pline") coords '("c")))
(setq currobj (ssadd (entlast) currobj))
(command "_layer" "set" "nitride" "")
(command "_layer" "set" "text" "")
(command "_circle" "3519.0625,-181.357" "0.075")
(command "_circle" "3519.0625,-181.057" "0.075")
(command "_circle" "3519.0625,-180.757" "0.075")
(command "_circle" "3519.0625,-180.457" "0.075")
(command "_circle" "3519.0625,-180.157" "0.075")
(command "_circle" "3518.7625,-181.357" "0.075")
(command "_circle" "3518.7625,-181.057" "0.075")
(command "_circle" "3518.7625,-180.757" "0.075")
(command "_circle" "3518.7625,-180.457" "0.075")
(command "_circle" "3518.7625,-180.157" "0.075")
(command "_circle" "3518.4625,-181.357" "0.075")
(command "_circle" "3518.4625,-181.057" "0.075")
(command "_circle" "3518.4625,-180.757" "0.075")
(command "_circle" "3518.4625,-180.457" "0.075")
(command "_circle" "3518.4625,-180.157" "0.075")
(command "_circle" "3518.1625,-181.357" "0.075")
(command "_circle" "3518.1625,-181.057" "0.075")
(command "_circle" "3518.1625,-180.757" "0.075")
(command "_circle" "3518.1625,-180.457" "0.075")
(command "_circle" "3518.1625,-180.157" "0.075")
(command "_circle" "3517.8625,-181.357" "0.075")
(command "_circle" "3517.8625,-181.057" "0.075")
(command "_circle" "3517.8625,-180.757" "0.075")
(command "_circle" "3517.8625,-180.457" "0.075")
(command "_circle" "3517.8625,-180.157" "0.075")
(command "_layer" "set" "nitride" "")
(setq coords (list 
(list 3520.2625 -155.914) 
(list 3520.2625 -40.2693) 
(list 3519.7375 -40.2693) 
(list 3519.7375 -155.914)))
(apply 'command (append '("pline") coords '("c")))
(setq currobj (ssadd (entlast) currobj))
(command "_layer" "set" "prebias" "")
(command "_rectangle" "3519.7375,-155.914" "3520.2625,-40.2693")
(setq currobj (ssadd (entlast) currobj))
(command "_layer" "set" "nitride" "")
(setq coords (list 
(list 3520.2625 -40.2693) 
(list 3520.5625 -30.2693) 
(list 3520.5625 -30.2693) 
(list 3520.5625 -29.2693) 
(list 3594.585 -30.0193) 
(list 3594.585 -25.0763) 
(list 3520.5625 -25.8263) 
(list 3520.5625 -24.8263) 
(list 3520.5625 -24.8263) 
(list 3520.2625 -14.8263) 
(list 3519.7375 -14.8263) 
(list 3519.4375 -24.8263) 
(list 3519.4375 -24.8263) 
(list 3519.4375 -25.8263) 
(list 3445.415 -25.0763) 
(list 3445.415 -30.0193) 
(list 3519.4375 -29.2693) 
(list 3519.4375 -30.2693) 
(list 3519.4375 -30.2693) 
(list 3519.7375 -40.2693)))
(apply 'command (append '("pline") coords '("c")))
(setq currobj (ssadd (entlast) currobj))
(command "_layer" "set" "prebias" "")
(setq coords (list 
(list 3519.4375 -40.2693) 
(list 3519.4375 -29.2693) 
(list 3445.415 -30.0193) 
(list 3445.415 -25.0763) 
(list 3519.4375 -25.8263) 
(list 3519.4375 -14.8263) 
(list 3520.5625 -14.8263) 
(list 3520.5625 -25.8263) 
(list 3594.585 -25.0763) 
(list 3594.585 -30.0193) 
(list 3520.5625 -29.2693) 
(list 3520.5625 -40.2693)))
(apply 'command (append '("pline") coords '("c")))
(setq currobj (ssadd (entlast) currobj))
(command "_layer" "set" "nitride" "")
(command "_layer" "set" "fda1" "")
(setq coords (list 
(list 3520.5625 -29.1263) 
(list 3594.585 -29.8763) 
(list 3594.585 -29.6993) 
(list 3520.5625 -29.0493)))
(apply 'command (append '("pline") coords '("c")))
(setq currobj (ssadd (entlast) currobj))
(setq coords (list 
(list 3520.5625 -28.9063) 
(list 3594.585 -29.5563) 
(list 3594.585 -29.3793) 
(list 3520.5625 -28.8293)))
(apply 'command (append '("pline") coords '("c")))
(setq currobj (ssadd (entlast) currobj))
(setq coords (list 
(list 3520.5625 -28.6863) 
(list 3594.585 -29.2363) 
(list 3594.585 -29.0593) 
(list 3520.5625 -28.6093)))
(apply 'command (append '("pline") coords '("c")))
(setq currobj (ssadd (entlast) currobj))
(setq coords (list 
(list 3520.5625 -28.4663) 
(list 3594.585 -28.9163) 
(list 3594.585 -28.7393) 
(list 3520.5625 -28.3893)))
(apply 'command (append '("pline") coords '("c")))
(setq currobj (ssadd (entlast) currobj))
(setq coords (list 
(list 3520.5625 -28.2463) 
(list 3594.585 -28.5963) 
(list 3594.585 -28.4193) 
(list 3520.5625 -28.1693)))
(apply 'command (append '("pline") coords '("c")))
(setq currobj (ssadd (entlast) currobj))
(setq coords (list 
(list 3520.5625 -28.0263) 
(list 3594.585 -28.2763) 
(list 3594.585 -28.0993) 
(list 3520.5625 -27.9493)))
(apply 'command (append '("pline") coords '("c")))
(setq currobj (ssadd (entlast) currobj))
(setq coords (list 
(list 3520.5625 -27.8063) 
(list 3594.585 -27.9563) 
(list 3594.585 -27.7793) 
(list 3520.5625 -27.7293)))
(apply 'command (append '("pline") coords '("c")))
(setq currobj (ssadd (entlast) currobj))
(setq coords (list 
(list 3520.5625 -27.5863) 
(list 3594.585 -27.6363) 
(list 3594.585 -27.4593) 
(list 3520.5625 -27.5093)))
(apply 'command (append '("pline") coords '("c")))
(setq currobj (ssadd (entlast) currobj))
(setq coords (list 
(list 3520.5625 -27.3663) 
(list 3594.585 -27.3163) 
(list 3594.585 -27.1393) 
(list 3520.5625 -27.2893)))
(apply 'command (append '("pline") coords '("c")))
(setq currobj (ssadd (entlast) currobj))
(setq coords (list 
(list 3520.5625 -27.1463) 
(list 3594.585 -26.9963) 
(list 3594.585 -26.8193) 
(list 3520.5625 -27.0693)))
(apply 'command (append '("pline") coords '("c")))
(setq currobj (ssadd (entlast) currobj))
(setq coords (list 
(list 3520.5625 -26.9263) 
(list 3594.585 -26.6763) 
(list 3594.585 -26.4993) 
(list 3520.5625 -26.8493)))
(apply 'command (append '("pline") coords '("c")))
(setq currobj (ssadd (entlast) currobj))
(setq coords (list 
(list 3520.5625 -26.7063) 
(list 3594.585 -26.3563) 
(list 3594.585 -26.1793) 
(list 3520.5625 -26.6293)))
(apply 'command (append '("pline") coords '("c")))
(setq currobj (ssadd (entlast) currobj))
(setq coords (list 
(list 3520.5625 -26.4863) 
(list 3594.585 -26.0363) 
(list 3594.585 -25.8593) 
(list 3520.5625 -26.4093)))
(apply 'command (append '("pline") coords '("c")))
(setq currobj (ssadd (entlast) currobj))
(setq coords (list 
(list 3520.5625 -26.2663) 
(list 3594.585 -25.7163) 
(list 3594.585 -25.5393) 
(list 3520.5625 -26.1893)))
(apply 'command (append '("pline") coords '("c")))
(setq currobj (ssadd (entlast) currobj))
(setq coords (list 
(list 3520.5625 -26.0463) 
(list 3594.585 -25.3963) 
(list 3594.585 -25.2193) 
(list 3520.5625 -25.9693)))
(apply 'command (append '("pline") coords '("c")))
(setq currobj (ssadd (entlast) currobj))
(setq coords (list 
(list 3519.4375 -25.9693) 
(list 3445.415 -25.2193) 
(list 3445.415 -25.3963) 
(list 3519.4375 -26.0463)))
(apply 'command (append '("pline") coords '("c")))
(setq currobj (ssadd (entlast) currobj))
(setq coords (list 
(list 3519.4375 -26.1893) 
(list 3445.415 -25.5393) 
(list 3445.415 -25.7163) 
(list 3519.4375 -26.2663)))
(apply 'command (append '("pline") coords '("c")))
(setq currobj (ssadd (entlast) currobj))
(setq coords (list 
(list 3519.4375 -26.4093) 
(list 3445.415 -25.8593) 
(list 3445.415 -26.0363) 
(list 3519.4375 -26.4863)))
(apply 'command (append '("pline") coords '("c")))
(setq currobj (ssadd (entlast) currobj))
(setq coords (list 
(list 3519.4375 -26.6293) 
(list 3445.415 -26.1793) 
(list 3445.415 -26.3563) 
(list 3519.4375 -26.7063)))
(apply 'command (append '("pline") coords '("c")))
(setq currobj (ssadd (entlast) currobj))
(setq coords (list 
(list 3519.4375 -26.8493) 
(list 3445.415 -26.4993) 
(list 3445.415 -26.6763) 
(list 3519.4375 -26.9263)))
(apply 'command (append '("pline") coords '("c")))
(setq currobj (ssadd (entlast) currobj))
(setq coords (list 
(list 3519.4375 -27.0693) 
(list 3445.415 -26.8193) 
(list 3445.415 -26.9963) 
(list 3519.4375 -27.1463)))
(apply 'command (append '("pline") coords '("c")))
(setq currobj (ssadd (entlast) currobj))
(setq coords (list 
(list 3519.4375 -27.2893) 
(list 3445.415 -27.1393) 
(list 3445.415 -27.3163) 
(list 3519.4375 -27.3663)))
(apply 'command (append '("pline") coords '("c")))
(setq currobj (ssadd (entlast) currobj))
(setq coords (list 
(list 3519.4375 -27.5093) 
(list 3445.415 -27.4593) 
(list 3445.415 -27.6363) 
(list 3519.4375 -27.5863)))
(apply 'command (append '("pline") coords '("c")))
(setq currobj (ssadd (entlast) currobj))
(setq coords (list 
(list 3519.4375 -27.7293) 
(list 3445.415 -27.7793) 
(list 3445.415 -27.9563) 
(list 3519.4375 -27.8063)))
(apply 'command (append '("pline") coords '("c")))
(setq currobj (ssadd (entlast) currobj))
(setq coords (list 
(list 3519.4375 -27.9493) 
(list 3445.415 -28.0993) 
(list 3445.415 -28.2763) 
(list 3519.4375 -28.0263)))
(apply 'command (append '("pline") coords '("c")))
(setq currobj (ssadd (entlast) currobj))
(setq coords (list 
(list 3519.4375 -28.1693) 
(list 3445.415 -28.4193) 
(list 3445.415 -28.5963) 
(list 3519.4375 -28.2463)))
(apply 'command (append '("pline") coords '("c")))
(setq currobj (ssadd (entlast) currobj))
(setq coords (list 
(list 3519.4375 -28.3893) 
(list 3445.415 -28.7393) 
(list 3445.415 -28.9163) 
(list 3519.4375 -28.4663)))
(apply 'command (append '("pline") coords '("c")))
(setq currobj (ssadd (entlast) currobj))
(setq coords (list 
(list 3519.4375 -28.6093) 
(list 3445.415 -29.0593) 
(list 3445.415 -29.2363) 
(list 3519.4375 -28.6863)))
(apply 'command (append '("pline") coords '("c")))
(setq currobj (ssadd (entlast) currobj))
(setq coords (list 
(list 3519.4375 -28.8293) 
(list 3445.415 -29.3793) 
(list 3445.415 -29.5563) 
(list 3519.4375 -28.9063)))
(apply 'command (append '("pline") coords '("c")))
(setq currobj (ssadd (entlast) currobj))
(setq coords (list 
(list 3519.4375 -29.0493) 
(list 3445.415 -29.6993) 
(list 3445.415 -29.8763) 
(list 3519.4375 -29.1263)))
(apply 'command (append '("pline") coords '("c")))
(setq currobj (ssadd (entlast) currobj))
(command "_layer" "set" "nitride" "")
(command "_layer" "set" "text" "")
(command "_circle" "3519.0625,-40.2693" "0.075")
(command "_circle" "3519.0625,-39.9693" "0.075")
(command "_circle" "3519.0625,-39.6693" "0.075")
(command "_circle" "3519.0625,-39.3693" "0.075")
(command "_circle" "3519.0625,-39.0693" "0.075")
(command "_circle" "3518.7625,-40.2693" "0.075")
(command "_circle" "3518.7625,-39.9693" "0.075")
(command "_circle" "3518.7625,-39.6693" "0.075")
(command "_circle" "3518.7625,-39.3693" "0.075")
(command "_circle" "3518.7625,-39.0693" "0.075")
(command "_circle" "3518.4625,-40.2693" "0.075")
(command "_circle" "3518.4625,-39.9693" "0.075")
(command "_circle" "3518.4625,-39.6693" "0.075")
(command "_circle" "3518.4625,-39.3693" "0.075")
(command "_circle" "3518.4625,-39.0693" "0.075")
(command "_circle" "3518.1625,-40.2693" "0.075")
(command "_circle" "3518.1625,-39.9693" "0.075")
(command "_circle" "3518.1625,-39.6693" "0.075")
(command "_circle" "3518.1625,-39.3693" "0.075")
(command "_circle" "3518.1625,-39.0693" "0.075")
(command "_circle" "3517.8625,-40.2693" "0.075")
(command "_circle" "3517.8625,-39.9693" "0.075")
(command "_circle" "3517.8625,-39.6693" "0.075")
(command "_circle" "3517.8625,-39.3693" "0.075")
(command "_circle" "3517.8625,-39.0693" "0.075")
(command "_layer" "set" "nitride" "")
(setq coords (list 
(list 3520.2625 -14.8263) 
(list 3520.2625 100.8184) 
(list 3519.7375 100.8184) 
(list 3519.7375 -14.8263)))
(apply 'command (append '("pline") coords '("c")))
(setq currobj (ssadd (entlast) currobj))
(command "_layer" "set" "prebias" "")
(command "_rectangle" "3519.7375,-14.8263" "3520.2625,100.8184")
(setq currobj (ssadd (entlast) currobj))
(command "_layer" "set" "nitride" "")
(setq coords (list 
(list 3520.2625 100.8184) 
(list 3520.5625 110.8184) 
(list 3520.5625 110.8184) 
(list 3520.5625 111.8184) 
(list 3594.585 111.0684) 
(list 3594.585 116.0114) 
(list 3520.5625 115.2614) 
(list 3520.5625 116.2614) 
(list 3520.5625 116.2614) 
(list 3520.2625 126.2614) 
(list 3519.7375 126.2614) 
(list 3519.4375 116.2614) 
(list 3519.4375 116.2614) 
(list 3519.4375 115.2614) 
(list 3445.415 116.0114) 
(list 3445.415 111.0684) 
(list 3519.4375 111.8184) 
(list 3519.4375 110.8184) 
(list 3519.4375 110.8184) 
(list 3519.7375 100.8184)))
(apply 'command (append '("pline") coords '("c")))
(setq currobj (ssadd (entlast) currobj))
(command "_layer" "set" "prebias" "")
(setq coords (list 
(list 3519.4375 100.8184) 
(list 3519.4375 111.8184) 
(list 3445.415 111.0684) 
(list 3445.415 116.0114) 
(list 3519.4375 115.2614) 
(list 3519.4375 126.2614) 
(list 3520.5625 126.2614) 
(list 3520.5625 115.2614) 
(list 3594.585 116.0114) 
(list 3594.585 111.0684) 
(list 3520.5625 111.8184) 
(list 3520.5625 100.8184)))
(apply 'command (append '("pline") coords '("c")))
(setq currobj (ssadd (entlast) currobj))
(command "_layer" "set" "nitride" "")
(command "_layer" "set" "fda1" "")
(setq coords (list 
(list 3520.5625 111.9614) 
(list 3594.585 111.2114) 
(list 3594.585 111.3884) 
(list 3520.5625 112.0384)))
(apply 'command (append '("pline") coords '("c")))
(setq currobj (ssadd (entlast) currobj))
(setq coords (list 
(list 3520.5625 112.1814) 
(list 3594.585 111.5314) 
(list 3594.585 111.7084) 
(list 3520.5625 112.2584)))
(apply 'command (append '("pline") coords '("c")))
(setq currobj (ssadd (entlast) currobj))
(setq coords (list 
(list 3520.5625 112.4014) 
(list 3594.585 111.8514) 
(list 3594.585 112.0284) 
(list 3520.5625 112.4784)))
(apply 'command (append '("pline") coords '("c")))
(setq currobj (ssadd (entlast) currobj))
(setq coords (list 
(list 3520.5625 112.6214) 
(list 3594.585 112.1714) 
(list 3594.585 112.3484) 
(list 3520.5625 112.6984)))
(apply 'command (append '("pline") coords '("c")))
(setq currobj (ssadd (entlast) currobj))
(setq coords (list 
(list 3520.5625 112.8414) 
(list 3594.585 112.4914) 
(list 3594.585 112.6684) 
(list 3520.5625 112.9184)))
(apply 'command (append '("pline") coords '("c")))
(setq currobj (ssadd (entlast) currobj))
(setq coords (list 
(list 3520.5625 113.0614) 
(list 3594.585 112.8114) 
(list 3594.585 112.9884) 
(list 3520.5625 113.1384)))
(apply 'command (append '("pline") coords '("c")))
(setq currobj (ssadd (entlast) currobj))
(setq coords (list 
(list 3520.5625 113.2814) 
(list 3594.585 113.1314) 
(list 3594.585 113.3084) 
(list 3520.5625 113.3584)))
(apply 'command (append '("pline") coords '("c")))
(setq currobj (ssadd (entlast) currobj))
(setq coords (list 
(list 3520.5625 113.5014) 
(list 3594.585 113.4514) 
(list 3594.585 113.6284) 
(list 3520.5625 113.5784)))
(apply 'command (append '("pline") coords '("c")))
(setq currobj (ssadd (entlast) currobj))
(setq coords (list 
(list 3520.5625 113.7214) 
(list 3594.585 113.7714) 
(list 3594.585 113.9484) 
(list 3520.5625 113.7984)))
(apply 'command (append '("pline") coords '("c")))
(setq currobj (ssadd (entlast) currobj))
(setq coords (list 
(list 3520.5625 113.9414) 
(list 3594.585 114.0914) 
(list 3594.585 114.2684) 
(list 3520.5625 114.0184)))
(apply 'command (append '("pline") coords '("c")))
(setq currobj (ssadd (entlast) currobj))
(setq coords (list 
(list 3520.5625 114.1614) 
(list 3594.585 114.4114) 
(list 3594.585 114.5884) 
(list 3520.5625 114.2384)))
(apply 'command (append '("pline") coords '("c")))
(setq currobj (ssadd (entlast) currobj))
(setq coords (list 
(list 3520.5625 114.3814) 
(list 3594.585 114.7314) 
(list 3594.585 114.9084) 
(list 3520.5625 114.4584)))
(apply 'command (append '("pline") coords '("c")))
(setq currobj (ssadd (entlast) currobj))
(setq coords (list 
(list 3520.5625 114.6014) 
(list 3594.585 115.0514) 
(list 3594.585 115.2284) 
(list 3520.5625 114.6784)))
(apply 'command (append '("pline") coords '("c")))
(setq currobj (ssadd (entlast) currobj))
(setq coords (list 
(list 3520.5625 114.8214) 
(list 3594.585 115.3714) 
(list 3594.585 115.5484) 
(list 3520.5625 114.8984)))
(apply 'command (append '("pline") coords '("c")))
(setq currobj (ssadd (entlast) currobj))
(setq coords (list 
(list 3520.5625 115.0414) 
(list 3594.585 115.6914) 
(list 3594.585 115.8684) 
(list 3520.5625 115.1184)))
(apply 'command (append '("pline") coords '("c")))
(setq currobj (ssadd (entlast) currobj))
(setq coords (list 
(list 3519.4375 115.1184) 
(list 3445.415 115.8684) 
(list 3445.415 115.6914) 
(list 3519.4375 115.0414)))
(apply 'command (append '("pline") coords '("c")))
(setq currobj (ssadd (entlast) currobj))
(setq coords (list 
(list 3519.4375 114.8984) 
(list 3445.415 115.5484) 
(list 3445.415 115.3714) 
(list 3519.4375 114.8214)))
(apply 'command (append '("pline") coords '("c")))
(setq currobj (ssadd (entlast) currobj))
(setq coords (list 
(list 3519.4375 114.6784) 
(list 3445.415 115.2284) 
(list 3445.415 115.0514) 
(list 3519.4375 114.6014)))
(apply 'command (append '("pline") coords '("c")))
(setq currobj (ssadd (entlast) currobj))
(setq coords (list 
(list 3519.4375 114.4584) 
(list 3445.415 114.9084) 
(list 3445.415 114.7314) 
(list 3519.4375 114.3814)))
(apply 'command (append '("pline") coords '("c")))
(setq currobj (ssadd (entlast) currobj))
(setq coords (list 
(list 3519.4375 114.2384) 
(list 3445.415 114.5884) 
(list 3445.415 114.4114) 
(list 3519.4375 114.1614)))
(apply 'command (append '("pline") coords '("c")))
(setq currobj (ssadd (entlast) currobj))
(setq coords (list 
(list 3519.4375 114.0184) 
(list 3445.415 114.2684) 
(list 3445.415 114.0914) 
(list 3519.4375 113.9414)))
(apply 'command (append '("pline") coords '("c")))
(setq currobj (ssadd (entlast) currobj))
(setq coords (list 
(list 3519.4375 113.7984) 
(list 3445.415 113.9484) 
(list 3445.415 113.7714) 
(list 3519.4375 113.7214)))
(apply 'command (append '("pline") coords '("c")))
(setq currobj (ssadd (entlast) currobj))
(setq coords (list 
(list 3519.4375 113.5784) 
(list 3445.415 113.6284) 
(list 3445.415 113.4514) 
(list 3519.4375 113.5014)))
(apply 'command (append '("pline") coords '("c")))
(setq currobj (ssadd (entlast) currobj))
(setq coords (list 
(list 3519.4375 113.3584) 
(list 3445.415 113.3084) 
(list 3445.415 113.1314) 
(list 3519.4375 113.2814)))
(apply 'command (append '("pline") coords '("c")))
(setq currobj (ssadd (entlast) currobj))
(setq coords (list 
(list 3519.4375 113.1384) 
(list 3445.415 112.9884) 
(list 3445.415 112.8114) 
(list 3519.4375 113.0614)))
(apply 'command (append '("pline") coords '("c")))
(setq currobj (ssadd (entlast) currobj))
(setq coords (list 
(list 3519.4375 112.9184) 
(list 3445.415 112.6684) 
(list 3445.415 112.4914) 
(list 3519.4375 112.8414)))
(apply 'command (append '("pline") coords '("c")))
(setq currobj (ssadd (entlast) currobj))
(setq coords (list 
(list 3519.4375 112.6984) 
(list 3445.415 112.3484) 
(list 3445.415 112.1714) 
(list 3519.4375 112.6214)))
(apply 'command (append '("pline") coords '("c")))
(setq currobj (ssadd (entlast) currobj))
(setq coords (list 
(list 3519.4375 112.4784) 
(list 3445.415 112.0284) 
(list 3445.415 111.8514) 
(list 3519.4375 112.4014)))
(apply 'command (append '("pline") coords '("c")))
(setq currobj (ssadd (entlast) currobj))
(setq coords (list 
(list 3519.4375 112.2584) 
(list 3445.415 111.7084) 
(list 3445.415 111.5314) 
(list 3519.4375 112.1814)))
(apply 'command (append '("pline") coords '("c")))
(setq currobj (ssadd (entlast) currobj))
(setq coords (list 
(list 3519.4375 112.0384) 
(list 3445.415 111.3884) 
(list 3445.415 111.2114) 
(list 3519.4375 111.9614)))
(apply 'command (append '("pline") coords '("c")))
(setq currobj (ssadd (entlast) currobj))
(command "_layer" "set" "nitride" "")
(command "_layer" "set" "text" "")
(command "_circle" "3519.0625,100.8184" "0.075")
(command "_circle" "3519.0625,101.1184" "0.075")
(command "_circle" "3519.0625,101.4184" "0.075")
(command "_circle" "3519.0625,101.7184" "0.075")
(command "_circle" "3519.0625,102.0184" "0.075")
(command "_circle" "3518.7625,100.8184" "0.075")
(command "_circle" "3518.7625,101.1184" "0.075")
(command "_circle" "3518.7625,101.4184" "0.075")
(command "_circle" "3518.7625,101.7184" "0.075")
(command "_circle" "3518.7625,102.0184" "0.075")
(command "_circle" "3518.4625,100.8184" "0.075")
(command "_circle" "3518.4625,101.1184" "0.075")
(command "_circle" "3518.4625,101.4184" "0.075")
(command "_circle" "3518.4625,101.7184" "0.075")
(command "_circle" "3518.4625,102.0184" "0.075")
(command "_circle" "3518.1625,100.8184" "0.075")
(command "_circle" "3518.1625,101.1184" "0.075")
(command "_circle" "3518.1625,101.4184" "0.075")
(command "_circle" "3518.1625,101.7184" "0.075")
(command "_circle" "3518.1625,102.0184" "0.075")
(command "_circle" "3517.8625,100.8184" "0.075")
(command "_circle" "3517.8625,101.1184" "0.075")
(command "_circle" "3517.8625,101.4184" "0.075")
(command "_circle" "3517.8625,101.7184" "0.075")
(command "_circle" "3517.8625,102.0184" "0.075")
(command "_layer" "set" "nitride" "")
(setq coords (list 
(list 3520.2625 126.2614) 
(list 3520.2625 241.9061) 
(list 3519.7375 241.9061) 
(list 3519.7375 126.2614)))
(apply 'command (append '("pline") coords '("c")))
(setq currobj (ssadd (entlast) currobj))
(command "_layer" "set" "prebias" "")
(command "_rectangle" "3519.7375,126.2614" "3520.2625,241.9061")
(setq currobj (ssadd (entlast) currobj))
(command "_layer" "set" "nitride" "")
(setq coords (list 
(list 3520.2625 241.9061) 
(list 3520.5625 251.9061) 
(list 3520.5625 251.9061) 
(list 3520.5625 252.9061) 
(list 3594.585 252.1561) 
(list 3594.585 257.0991) 
(list 3520.5625 256.3491) 
(list 3520.5625 257.3491) 
(list 3520.5625 257.3491) 
(list 3520.2625 267.3491) 
(list 3519.7375 267.3491) 
(list 3519.4375 257.3491) 
(list 3519.4375 257.3491) 
(list 3519.4375 256.3491) 
(list 3445.415 257.0991) 
(list 3445.415 252.1561) 
(list 3519.4375 252.9061) 
(list 3519.4375 251.9061) 
(list 3519.4375 251.9061) 
(list 3519.7375 241.9061)))
(apply 'command (append '("pline") coords '("c")))
(setq currobj (ssadd (entlast) currobj))
(command "_layer" "set" "prebias" "")
(setq coords (list 
(list 3519.4375 241.9061) 
(list 3519.4375 252.9061) 
(list 3445.415 252.1561) 
(list 3445.415 257.0991) 
(list 3519.4375 256.3491) 
(list 3519.4375 267.3491) 
(list 3520.5625 267.3491) 
(list 3520.5625 256.3491) 
(list 3594.585 257.0991) 
(list 3594.585 252.1561) 
(list 3520.5625 252.9061) 
(list 3520.5625 241.9061)))
(apply 'command (append '("pline") coords '("c")))
(setq currobj (ssadd (entlast) currobj))
(command "_layer" "set" "nitride" "")
(command "_layer" "set" "fda1" "")
(setq coords (list 
(list 3520.5625 253.0491) 
(list 3594.585 252.2991) 
(list 3594.585 252.4761) 
(list 3520.5625 253.1261)))
(apply 'command (append '("pline") coords '("c")))
(setq currobj (ssadd (entlast) currobj))
(setq coords (list 
(list 3520.5625 253.2691) 
(list 3594.585 252.6191) 
(list 3594.585 252.7961) 
(list 3520.5625 253.3461)))
(apply 'command (append '("pline") coords '("c")))
(setq currobj (ssadd (entlast) currobj))
(setq coords (list 
(list 3520.5625 253.4891) 
(list 3594.585 252.9391) 
(list 3594.585 253.1161) 
(list 3520.5625 253.5661)))
(apply 'command (append '("pline") coords '("c")))
(setq currobj (ssadd (entlast) currobj))
(setq coords (list 
(list 3520.5625 253.7091) 
(list 3594.585 253.2591) 
(list 3594.585 253.4361) 
(list 3520.5625 253.7861)))
(apply 'command (append '("pline") coords '("c")))
(setq currobj (ssadd (entlast) currobj))
(setq coords (list 
(list 3520.5625 253.9291) 
(list 3594.585 253.5791) 
(list 3594.585 253.7561) 
(list 3520.5625 254.0061)))
(apply 'command (append '("pline") coords '("c")))
(setq currobj (ssadd (entlast) currobj))
(setq coords (list 
(list 3520.5625 254.1491) 
(list 3594.585 253.8991) 
(list 3594.585 254.0761) 
(list 3520.5625 254.2261)))
(apply 'command (append '("pline") coords '("c")))
(setq currobj (ssadd (entlast) currobj))
(setq coords (list 
(list 3520.5625 254.3691) 
(list 3594.585 254.2191) 
(list 3594.585 254.3961) 
(list 3520.5625 254.4461)))
(apply 'command (append '("pline") coords '("c")))
(setq currobj (ssadd (entlast) currobj))
(setq coords (list 
(list 3520.5625 254.5891) 
(list 3594.585 254.5391) 
(list 3594.585 254.7161) 
(list 3520.5625 254.6661)))
(apply 'command (append '("pline") coords '("c")))
(setq currobj (ssadd (entlast) currobj))
(setq coords (list 
(list 3520.5625 254.8091) 
(list 3594.585 254.8591) 
(list 3594.585 255.0361) 
(list 3520.5625 254.8861)))
(apply 'command (append '("pline") coords '("c")))
(setq currobj (ssadd (entlast) currobj))
(setq coords (list 
(list 3520.5625 255.0291) 
(list 3594.585 255.1791) 
(list 3594.585 255.3561) 
(list 3520.5625 255.1061)))
(apply 'command (append '("pline") coords '("c")))
(setq currobj (ssadd (entlast) currobj))
(setq coords (list 
(list 3520.5625 255.2491) 
(list 3594.585 255.4991) 
(list 3594.585 255.6761) 
(list 3520.5625 255.3261)))
(apply 'command (append '("pline") coords '("c")))
(setq currobj (ssadd (entlast) currobj))
(setq coords (list 
(list 3520.5625 255.4691) 
(list 3594.585 255.8191) 
(list 3594.585 255.9961) 
(list 3520.5625 255.5461)))
(apply 'command (append '("pline") coords '("c")))
(setq currobj (ssadd (entlast) currobj))
(setq coords (list 
(list 3520.5625 255.6891) 
(list 3594.585 256.1391) 
(list 3594.585 256.3161) 
(list 3520.5625 255.7661)))
(apply 'command (append '("pline") coords '("c")))
(setq currobj (ssadd (entlast) currobj))
(setq coords (list 
(list 3520.5625 255.9091) 
(list 3594.585 256.4591) 
(list 3594.585 256.6361) 
(list 3520.5625 255.9861)))
(apply 'command (append '("pline") coords '("c")))
(setq currobj (ssadd (entlast) currobj))
(setq coords (list 
(list 3520.5625 256.1291) 
(list 3594.585 256.7791) 
(list 3594.585 256.9561) 
(list 3520.5625 256.2061)))
(apply 'command (append '("pline") coords '("c")))
(setq currobj (ssadd (entlast) currobj))
(setq coords (list 
(list 3519.4375 256.2061) 
(list 3445.415 256.9561) 
(list 3445.415 256.7791) 
(list 3519.4375 256.1291)))
(apply 'command (append '("pline") coords '("c")))
(setq currobj (ssadd (entlast) currobj))
(setq coords (list 
(list 3519.4375 255.9861) 
(list 3445.415 256.6361) 
(list 3445.415 256.4591) 
(list 3519.4375 255.9091)))
(apply 'command (append '("pline") coords '("c")))
(setq currobj (ssadd (entlast) currobj))
(setq coords (list 
(list 3519.4375 255.7661) 
(list 3445.415 256.3161) 
(list 3445.415 256.1391) 
(list 3519.4375 255.6891)))
(apply 'command (append '("pline") coords '("c")))
(setq currobj (ssadd (entlast) currobj))
(setq coords (list 
(list 3519.4375 255.5461) 
(list 3445.415 255.9961) 
(list 3445.415 255.8191) 
(list 3519.4375 255.4691)))
(apply 'command (append '("pline") coords '("c")))
(setq currobj (ssadd (entlast) currobj))
(setq coords (list 
(list 3519.4375 255.3261) 
(list 3445.415 255.6761) 
(list 3445.415 255.4991) 
(list 3519.4375 255.2491)))
(apply 'command (append '("pline") coords '("c")))
(setq currobj (ssadd (entlast) currobj))
(setq coords (list 
(list 3519.4375 255.1061) 
(list 3445.415 255.3561) 
(list 3445.415 255.1791) 
(list 3519.4375 255.0291)))
(apply 'command (append '("pline") coords '("c")))
(setq currobj (ssadd (entlast) currobj))
(setq coords (list 
(list 3519.4375 254.8861) 
(list 3445.415 255.0361) 
(list 3445.415 254.8591) 
(list 3519.4375 254.8091)))
(apply 'command (append '("pline") coords '("c")))
(setq currobj (ssadd (entlast) currobj))
(setq coords (list 
(list 3519.4375 254.6661) 
(list 3445.415 254.7161) 
(list 3445.415 254.5391) 
(list 3519.4375 254.5891)))
(apply 'command (append '("pline") coords '("c")))
(setq currobj (ssadd (entlast) currobj))
(setq coords (list 
(list 3519.4375 254.4461) 
(list 3445.415 254.3961) 
(list 3445.415 254.2191) 
(list 3519.4375 254.3691)))
(apply 'command (append '("pline") coords '("c")))
(setq currobj (ssadd (entlast) currobj))
(setq coords (list 
(list 3519.4375 254.2261) 
(list 3445.415 254.0761) 
(list 3445.415 253.8991) 
(list 3519.4375 254.1491)))
(apply 'command (append '("pline") coords '("c")))
(setq currobj (ssadd (entlast) currobj))
(setq coords (list 
(list 3519.4375 254.0061) 
(list 3445.415 253.7561) 
(list 3445.415 253.5791) 
(list 3519.4375 253.9291)))
(apply 'command (append '("pline") coords '("c")))
(setq currobj (ssadd (entlast) currobj))
(setq coords (list 
(list 3519.4375 253.7861) 
(list 3445.415 253.4361) 
(list 3445.415 253.2591) 
(list 3519.4375 253.7091)))
(apply 'command (append '("pline") coords '("c")))
(setq currobj (ssadd (entlast) currobj))
(setq coords (list 
(list 3519.4375 253.5661) 
(list 3445.415 253.1161) 
(list 3445.415 252.9391) 
(list 3519.4375 253.4891)))
(apply 'command (append '("pline") coords '("c")))
(setq currobj (ssadd (entlast) currobj))
(setq coords (list 
(list 3519.4375 253.3461) 
(list 3445.415 252.7961) 
(list 3445.415 252.6191) 
(list 3519.4375 253.2691)))
(apply 'command (append '("pline") coords '("c")))
(setq currobj (ssadd (entlast) currobj))
(setq coords (list 
(list 3519.4375 253.1261) 
(list 3445.415 252.4761) 
(list 3445.415 252.2991) 
(list 3519.4375 253.0491)))
(apply 'command (append '("pline") coords '("c")))
(setq currobj (ssadd (entlast) currobj))
(command "_layer" "set" "nitride" "")
(command "_layer" "set" "text" "")
(command "_circle" "3519.0625,241.9061" "0.075")
(command "_circle" "3519.0625,242.2061" "0.075")
(command "_circle" "3519.0625,242.5061" "0.075")
(command "_circle" "3519.0625,242.8061" "0.075")
(command "_circle" "3519.0625,243.1061" "0.075")
(command "_circle" "3518.7625,241.9061" "0.075")
(command "_circle" "3518.7625,242.2061" "0.075")
(command "_circle" "3518.7625,242.5061" "0.075")
(command "_circle" "3518.7625,242.8061" "0.075")
(command "_circle" "3518.7625,243.1061" "0.075")
(command "_circle" "3518.4625,241.9061" "0.075")
(command "_circle" "3518.4625,242.2061" "0.075")
(command "_circle" "3518.4625,242.5061" "0.075")
(command "_circle" "3518.4625,242.8061" "0.075")
(command "_circle" "3518.4625,243.1061" "0.075")
(command "_circle" "3518.1625,241.9061" "0.075")
(command "_circle" "3518.1625,242.2061" "0.075")
(command "_circle" "3518.1625,242.5061" "0.075")
(command "_circle" "3518.1625,242.8061" "0.075")
(command "_circle" "3518.1625,243.1061" "0.075")
(command "_circle" "3517.8625,241.9061" "0.075")
(command "_circle" "3517.8625,242.2061" "0.075")
(command "_circle" "3517.8625,242.5061" "0.075")
(command "_circle" "3517.8625,242.8061" "0.075")
(command "_circle" "3517.8625,243.1061" "0.075")
(command "_layer" "set" "nitride" "")
(setq coords (list 
(list 3520.2625 267.3491) 
(list 3520.2625 382.9939) 
(list 3519.7375 382.9939) 
(list 3519.7375 267.3491)))
(apply 'command (append '("pline") coords '("c")))
(setq currobj (ssadd (entlast) currobj))
(command "_layer" "set" "prebias" "")
(command "_rectangle" "3519.7375,267.3491" "3520.2625,382.9939")
(setq currobj (ssadd (entlast) currobj))
(command "_layer" "set" "nitride" "")
(setq coords (list 
(list 3520.2625 382.9939) 
(list 3520.5625 392.9939) 
(list 3520.5625 392.9939) 
(list 3520.5625 393.9939) 
(list 3594.585 393.2439) 
(list 3594.585 398.1869) 
(list 3520.5625 397.4369) 
(list 3520.5625 398.4369) 
(list 3520.5625 398.4369) 
(list 3520.2625 408.4369) 
(list 3519.7375 408.4369) 
(list 3519.4375 398.4369) 
(list 3519.4375 398.4369) 
(list 3519.4375 397.4369) 
(list 3445.415 398.1869) 
(list 3445.415 393.2439) 
(list 3519.4375 393.9939) 
(list 3519.4375 392.9939) 
(list 3519.4375 392.9939) 
(list 3519.7375 382.9939)))
(apply 'command (append '("pline") coords '("c")))
(setq currobj (ssadd (entlast) currobj))
(command "_layer" "set" "prebias" "")
(setq coords (list 
(list 3519.4375 382.9939) 
(list 3519.4375 393.9939) 
(list 3445.415 393.2439) 
(list 3445.415 398.1869) 
(list 3519.4375 397.4369) 
(list 3519.4375 408.4369) 
(list 3520.5625 408.4369) 
(list 3520.5625 397.4369) 
(list 3594.585 398.1869) 
(list 3594.585 393.2439) 
(list 3520.5625 393.9939) 
(list 3520.5625 382.9939)))
(apply 'command (append '("pline") coords '("c")))
(setq currobj (ssadd (entlast) currobj))
(command "_layer" "set" "nitride" "")
(command "_layer" "set" "fda1" "")
(setq coords (list 
(list 3520.5625 394.1369) 
(list 3594.585 393.3869) 
(list 3594.585 393.5639) 
(list 3520.5625 394.2139)))
(apply 'command (append '("pline") coords '("c")))
(setq currobj (ssadd (entlast) currobj))
(setq coords (list 
(list 3520.5625 394.3569) 
(list 3594.585 393.7069) 
(list 3594.585 393.8839) 
(list 3520.5625 394.4339)))
(apply 'command (append '("pline") coords '("c")))
(setq currobj (ssadd (entlast) currobj))
(setq coords (list 
(list 3520.5625 394.5769) 
(list 3594.585 394.0269) 
(list 3594.585 394.2039) 
(list 3520.5625 394.6539)))
(apply 'command (append '("pline") coords '("c")))
(setq currobj (ssadd (entlast) currobj))
(setq coords (list 
(list 3520.5625 394.7969) 
(list 3594.585 394.3469) 
(list 3594.585 394.5239) 
(list 3520.5625 394.8739)))
(apply 'command (append '("pline") coords '("c")))
(setq currobj (ssadd (entlast) currobj))
(setq coords (list 
(list 3520.5625 395.0169) 
(list 3594.585 394.6669) 
(list 3594.585 394.8439) 
(list 3520.5625 395.0939)))
(apply 'command (append '("pline") coords '("c")))
(setq currobj (ssadd (entlast) currobj))
(setq coords (list 
(list 3520.5625 395.2369) 
(list 3594.585 394.9869) 
(list 3594.585 395.1639) 
(list 3520.5625 395.3139)))
(apply 'command (append '("pline") coords '("c")))
(setq currobj (ssadd (entlast) currobj))
(setq coords (list 
(list 3520.5625 395.4569) 
(list 3594.585 395.3069) 
(list 3594.585 395.4839) 
(list 3520.5625 395.5339)))
(apply 'command (append '("pline") coords '("c")))
(setq currobj (ssadd (entlast) currobj))
(setq coords (list 
(list 3520.5625 395.6769) 
(list 3594.585 395.6269) 
(list 3594.585 395.8039) 
(list 3520.5625 395.7539)))
(apply 'command (append '("pline") coords '("c")))
(setq currobj (ssadd (entlast) currobj))
(setq coords (list 
(list 3520.5625 395.8969) 
(list 3594.585 395.9469) 
(list 3594.585 396.1239) 
(list 3520.5625 395.9739)))
(apply 'command (append '("pline") coords '("c")))
(setq currobj (ssadd (entlast) currobj))
(setq coords (list 
(list 3520.5625 396.1169) 
(list 3594.585 396.2669) 
(list 3594.585 396.4439) 
(list 3520.5625 396.1939)))
(apply 'command (append '("pline") coords '("c")))
(setq currobj (ssadd (entlast) currobj))
(setq coords (list 
(list 3520.5625 396.3369) 
(list 3594.585 396.5869) 
(list 3594.585 396.7639) 
(list 3520.5625 396.4139)))
(apply 'command (append '("pline") coords '("c")))
(setq currobj (ssadd (entlast) currobj))
(setq coords (list 
(list 3520.5625 396.5569) 
(list 3594.585 396.9069) 
(list 3594.585 397.0839) 
(list 3520.5625 396.6339)))
(apply 'command (append '("pline") coords '("c")))
(setq currobj (ssadd (entlast) currobj))
(setq coords (list 
(list 3520.5625 396.7769) 
(list 3594.585 397.2269) 
(list 3594.585 397.4039) 
(list 3520.5625 396.8539)))
(apply 'command (append '("pline") coords '("c")))
(setq currobj (ssadd (entlast) currobj))
(setq coords (list 
(list 3520.5625 396.9969) 
(list 3594.585 397.5469) 
(list 3594.585 397.7239) 
(list 3520.5625 397.0739)))
(apply 'command (append '("pline") coords '("c")))
(setq currobj (ssadd (entlast) currobj))
(setq coords (list 
(list 3520.5625 397.2169) 
(list 3594.585 397.8669) 
(list 3594.585 398.0439) 
(list 3520.5625 397.2939)))
(apply 'command (append '("pline") coords '("c")))
(setq currobj (ssadd (entlast) currobj))
(setq coords (list 
(list 3519.4375 397.2939) 
(list 3445.415 398.0439) 
(list 3445.415 397.8669) 
(list 3519.4375 397.2169)))
(apply 'command (append '("pline") coords '("c")))
(setq currobj (ssadd (entlast) currobj))
(setq coords (list 
(list 3519.4375 397.0739) 
(list 3445.415 397.7239) 
(list 3445.415 397.5469) 
(list 3519.4375 396.9969)))
(apply 'command (append '("pline") coords '("c")))
(setq currobj (ssadd (entlast) currobj))
(setq coords (list 
(list 3519.4375 396.8539) 
(list 3445.415 397.4039) 
(list 3445.415 397.2269) 
(list 3519.4375 396.7769)))
(apply 'command (append '("pline") coords '("c")))
(setq currobj (ssadd (entlast) currobj))
(setq coords (list 
(list 3519.4375 396.6339) 
(list 3445.415 397.0839) 
(list 3445.415 396.9069) 
(list 3519.4375 396.5569)))
(apply 'command (append '("pline") coords '("c")))
(setq currobj (ssadd (entlast) currobj))
(setq coords (list 
(list 3519.4375 396.4139) 
(list 3445.415 396.7639) 
(list 3445.415 396.5869) 
(list 3519.4375 396.3369)))
(apply 'command (append '("pline") coords '("c")))
(setq currobj (ssadd (entlast) currobj))
(setq coords (list 
(list 3519.4375 396.1939) 
(list 3445.415 396.4439) 
(list 3445.415 396.2669) 
(list 3519.4375 396.1169)))
(apply 'command (append '("pline") coords '("c")))
(setq currobj (ssadd (entlast) currobj))
(setq coords (list 
(list 3519.4375 395.9739) 
(list 3445.415 396.1239) 
(list 3445.415 395.9469) 
(list 3519.4375 395.8969)))
(apply 'command (append '("pline") coords '("c")))
(setq currobj (ssadd (entlast) currobj))
(setq coords (list 
(list 3519.4375 395.7539) 
(list 3445.415 395.8039) 
(list 3445.415 395.6269) 
(list 3519.4375 395.6769)))
(apply 'command (append '("pline") coords '("c")))
(setq currobj (ssadd (entlast) currobj))
(setq coords (list 
(list 3519.4375 395.5339) 
(list 3445.415 395.4839) 
(list 3445.415 395.3069) 
(list 3519.4375 395.4569)))
(apply 'command (append '("pline") coords '("c")))
(setq currobj (ssadd (entlast) currobj))
(setq coords (list 
(list 3519.4375 395.3139) 
(list 3445.415 395.1639) 
(list 3445.415 394.9869) 
(list 3519.4375 395.2369)))
(apply 'command (append '("pline") coords '("c")))
(setq currobj (ssadd (entlast) currobj))
(setq coords (list 
(list 3519.4375 395.0939) 
(list 3445.415 394.8439) 
(list 3445.415 394.6669) 
(list 3519.4375 395.0169)))
(apply 'command (append '("pline") coords '("c")))
(setq currobj (ssadd (entlast) currobj))
(setq coords (list 
(list 3519.4375 394.8739) 
(list 3445.415 394.5239) 
(list 3445.415 394.3469) 
(list 3519.4375 394.7969)))
(apply 'command (append '("pline") coords '("c")))
(setq currobj (ssadd (entlast) currobj))
(setq coords (list 
(list 3519.4375 394.6539) 
(list 3445.415 394.2039) 
(list 3445.415 394.0269) 
(list 3519.4375 394.5769)))
(apply 'command (append '("pline") coords '("c")))
(setq currobj (ssadd (entlast) currobj))
(setq coords (list 
(list 3519.4375 394.4339) 
(list 3445.415 393.8839) 
(list 3445.415 393.7069) 
(list 3519.4375 394.3569)))
(apply 'command (append '("pline") coords '("c")))
(setq currobj (ssadd (entlast) currobj))
(setq coords (list 
(list 3519.4375 394.2139) 
(list 3445.415 393.5639) 
(list 3445.415 393.3869) 
(list 3519.4375 394.1369)))
(apply 'command (append '("pline") coords '("c")))
(setq currobj (ssadd (entlast) currobj))
(command "_layer" "set" "nitride" "")
(command "_layer" "set" "text" "")
(command "_circle" "3519.0625,382.9939" "0.075")
(command "_circle" "3519.0625,383.2939" "0.075")
(command "_circle" "3519.0625,383.5939" "0.075")
(command "_circle" "3519.0625,383.8939" "0.075")
(command "_circle" "3519.0625,384.1939" "0.075")
(command "_circle" "3518.7625,382.9939" "0.075")
(command "_circle" "3518.7625,383.2939" "0.075")
(command "_circle" "3518.7625,383.5939" "0.075")
(command "_circle" "3518.7625,383.8939" "0.075")
(command "_circle" "3518.7625,384.1939" "0.075")
(command "_circle" "3518.4625,382.9939" "0.075")
(command "_circle" "3518.4625,383.2939" "0.075")
(command "_circle" "3518.4625,383.5939" "0.075")
(command "_circle" "3518.4625,383.8939" "0.075")
(command "_circle" "3518.4625,384.1939" "0.075")
(command "_circle" "3518.1625,382.9939" "0.075")
(command "_circle" "3518.1625,383.2939" "0.075")
(command "_circle" "3518.1625,383.5939" "0.075")
(command "_circle" "3518.1625,383.8939" "0.075")
(command "_circle" "3518.1625,384.1939" "0.075")
(command "_circle" "3517.8625,382.9939" "0.075")
(command "_circle" "3517.8625,383.2939" "0.075")
(command "_circle" "3517.8625,383.5939" "0.075")
(command "_circle" "3517.8625,383.8939" "0.075")
(command "_circle" "3517.8625,384.1939" "0.075")
(command "_layer" "set" "nitride" "")
(setq coords (list 
(list 3520.2625 408.4369) 
(list 3520.2625 524.0816) 
(list 3519.7375 524.0816) 
(list 3519.7375 408.4369)))
(apply 'command (append '("pline") coords '("c")))
(setq currobj (ssadd (entlast) currobj))
(command "_layer" "set" "prebias" "")
(command "_rectangle" "3519.7375,408.4369" "3520.2625,524.0816")
(setq currobj (ssadd (entlast) currobj))
(command "_layer" "set" "nitride" "")
(setq coords (list 
(list 3520.2625 524.0816) 
(list 3520.5625 534.0816) 
(list 3520.5625 534.0816) 
(list 3520.5625 535.0816) 
(list 3594.585 534.3316) 
(list 3594.585 539.2746) 
(list 3520.5625 538.5246) 
(list 3520.5625 539.5246) 
(list 3520.5625 539.5246) 
(list 3520.2625 549.5246) 
(list 3519.7375 549.5246) 
(list 3519.4375 539.5246) 
(list 3519.4375 539.5246) 
(list 3519.4375 538.5246) 
(list 3445.415 539.2746) 
(list 3445.415 534.3316) 
(list 3519.4375 535.0816) 
(list 3519.4375 534.0816) 
(list 3519.4375 534.0816) 
(list 3519.7375 524.0816)))
(apply 'command (append '("pline") coords '("c")))
(setq currobj (ssadd (entlast) currobj))
(command "_layer" "set" "prebias" "")
(setq coords (list 
(list 3519.4375 524.0816) 
(list 3519.4375 535.0816) 
(list 3445.415 534.3316) 
(list 3445.415 539.2746) 
(list 3519.4375 538.5246) 
(list 3519.4375 549.5246) 
(list 3520.5625 549.5246) 
(list 3520.5625 538.5246) 
(list 3594.585 539.2746) 
(list 3594.585 534.3316) 
(list 3520.5625 535.0816) 
(list 3520.5625 524.0816)))
(apply 'command (append '("pline") coords '("c")))
(setq currobj (ssadd (entlast) currobj))
(command "_layer" "set" "nitride" "")
(command "_layer" "set" "fda1" "")
(setq coords (list 
(list 3520.5625 535.2246) 
(list 3594.585 534.4746) 
(list 3594.585 534.6516) 
(list 3520.5625 535.3016)))
(apply 'command (append '("pline") coords '("c")))
(setq currobj (ssadd (entlast) currobj))
(setq coords (list 
(list 3520.5625 535.4446) 
(list 3594.585 534.7946) 
(list 3594.585 534.9716) 
(list 3520.5625 535.5216)))
(apply 'command (append '("pline") coords '("c")))
(setq currobj (ssadd (entlast) currobj))
(setq coords (list 
(list 3520.5625 535.6646) 
(list 3594.585 535.1146) 
(list 3594.585 535.2916) 
(list 3520.5625 535.7416)))
(apply 'command (append '("pline") coords '("c")))
(setq currobj (ssadd (entlast) currobj))
(setq coords (list 
(list 3520.5625 535.8846) 
(list 3594.585 535.4346) 
(list 3594.585 535.6116) 
(list 3520.5625 535.9616)))
(apply 'command (append '("pline") coords '("c")))
(setq currobj (ssadd (entlast) currobj))
(setq coords (list 
(list 3520.5625 536.1046) 
(list 3594.585 535.7546) 
(list 3594.585 535.9316) 
(list 3520.5625 536.1816)))
(apply 'command (append '("pline") coords '("c")))
(setq currobj (ssadd (entlast) currobj))
(setq coords (list 
(list 3520.5625 536.3246) 
(list 3594.585 536.0746) 
(list 3594.585 536.2516) 
(list 3520.5625 536.4016)))
(apply 'command (append '("pline") coords '("c")))
(setq currobj (ssadd (entlast) currobj))
(setq coords (list 
(list 3520.5625 536.5446) 
(list 3594.585 536.3946) 
(list 3594.585 536.5716) 
(list 3520.5625 536.6216)))
(apply 'command (append '("pline") coords '("c")))
(setq currobj (ssadd (entlast) currobj))
(setq coords (list 
(list 3520.5625 536.7646) 
(list 3594.585 536.7146) 
(list 3594.585 536.8916) 
(list 3520.5625 536.8416)))
(apply 'command (append '("pline") coords '("c")))
(setq currobj (ssadd (entlast) currobj))
(setq coords (list 
(list 3520.5625 536.9846) 
(list 3594.585 537.0346) 
(list 3594.585 537.2116) 
(list 3520.5625 537.0616)))
(apply 'command (append '("pline") coords '("c")))
(setq currobj (ssadd (entlast) currobj))
(setq coords (list 
(list 3520.5625 537.2046) 
(list 3594.585 537.3546) 
(list 3594.585 537.5316) 
(list 3520.5625 537.2816)))
(apply 'command (append '("pline") coords '("c")))
(setq currobj (ssadd (entlast) currobj))
(setq coords (list 
(list 3520.5625 537.4246) 
(list 3594.585 537.6746) 
(list 3594.585 537.8516) 
(list 3520.5625 537.5016)))
(apply 'command (append '("pline") coords '("c")))
(setq currobj (ssadd (entlast) currobj))
(setq coords (list 
(list 3520.5625 537.6446) 
(list 3594.585 537.9946) 
(list 3594.585 538.1716) 
(list 3520.5625 537.7216)))
(apply 'command (append '("pline") coords '("c")))
(setq currobj (ssadd (entlast) currobj))
(setq coords (list 
(list 3520.5625 537.8646) 
(list 3594.585 538.3146) 
(list 3594.585 538.4916) 
(list 3520.5625 537.9416)))
(apply 'command (append '("pline") coords '("c")))
(setq currobj (ssadd (entlast) currobj))
(setq coords (list 
(list 3520.5625 538.0846) 
(list 3594.585 538.6346) 
(list 3594.585 538.8116) 
(list 3520.5625 538.1616)))
(apply 'command (append '("pline") coords '("c")))
(setq currobj (ssadd (entlast) currobj))
(setq coords (list 
(list 3520.5625 538.3046) 
(list 3594.585 538.9546) 
(list 3594.585 539.1316) 
(list 3520.5625 538.3816)))
(apply 'command (append '("pline") coords '("c")))
(setq currobj (ssadd (entlast) currobj))
(setq coords (list 
(list 3519.4375 538.3816) 
(list 3445.415 539.1316) 
(list 3445.415 538.9546) 
(list 3519.4375 538.3046)))
(apply 'command (append '("pline") coords '("c")))
(setq currobj (ssadd (entlast) currobj))
(setq coords (list 
(list 3519.4375 538.1616) 
(list 3445.415 538.8116) 
(list 3445.415 538.6346) 
(list 3519.4375 538.0846)))
(apply 'command (append '("pline") coords '("c")))
(setq currobj (ssadd (entlast) currobj))
(setq coords (list 
(list 3519.4375 537.9416) 
(list 3445.415 538.4916) 
(list 3445.415 538.3146) 
(list 3519.4375 537.8646)))
(apply 'command (append '("pline") coords '("c")))
(setq currobj (ssadd (entlast) currobj))
(setq coords (list 
(list 3519.4375 537.7216) 
(list 3445.415 538.1716) 
(list 3445.415 537.9946) 
(list 3519.4375 537.6446)))
(apply 'command (append '("pline") coords '("c")))
(setq currobj (ssadd (entlast) currobj))
(setq coords (list 
(list 3519.4375 537.5016) 
(list 3445.415 537.8516) 
(list 3445.415 537.6746) 
(list 3519.4375 537.4246)))
(apply 'command (append '("pline") coords '("c")))
(setq currobj (ssadd (entlast) currobj))
(setq coords (list 
(list 3519.4375 537.2816) 
(list 3445.415 537.5316) 
(list 3445.415 537.3546) 
(list 3519.4375 537.2046)))
(apply 'command (append '("pline") coords '("c")))
(setq currobj (ssadd (entlast) currobj))
(setq coords (list 
(list 3519.4375 537.0616) 
(list 3445.415 537.2116) 
(list 3445.415 537.0346) 
(list 3519.4375 536.9846)))
(apply 'command (append '("pline") coords '("c")))
(setq currobj (ssadd (entlast) currobj))
(setq coords (list 
(list 3519.4375 536.8416) 
(list 3445.415 536.8916) 
(list 3445.415 536.7146) 
(list 3519.4375 536.7646)))
(apply 'command (append '("pline") coords '("c")))
(setq currobj (ssadd (entlast) currobj))
(setq coords (list 
(list 3519.4375 536.6216) 
(list 3445.415 536.5716) 
(list 3445.415 536.3946) 
(list 3519.4375 536.5446)))
(apply 'command (append '("pline") coords '("c")))
(setq currobj (ssadd (entlast) currobj))
(setq coords (list 
(list 3519.4375 536.4016) 
(list 3445.415 536.2516) 
(list 3445.415 536.0746) 
(list 3519.4375 536.3246)))
(apply 'command (append '("pline") coords '("c")))
(setq currobj (ssadd (entlast) currobj))
(setq coords (list 
(list 3519.4375 536.1816) 
(list 3445.415 535.9316) 
(list 3445.415 535.7546) 
(list 3519.4375 536.1046)))
(apply 'command (append '("pline") coords '("c")))
(setq currobj (ssadd (entlast) currobj))
(setq coords (list 
(list 3519.4375 535.9616) 
(list 3445.415 535.6116) 
(list 3445.415 535.4346) 
(list 3519.4375 535.8846)))
(apply 'command (append '("pline") coords '("c")))
(setq currobj (ssadd (entlast) currobj))
(setq coords (list 
(list 3519.4375 535.7416) 
(list 3445.415 535.2916) 
(list 3445.415 535.1146) 
(list 3519.4375 535.6646)))
(apply 'command (append '("pline") coords '("c")))
(setq currobj (ssadd (entlast) currobj))
(setq coords (list 
(list 3519.4375 535.5216) 
(list 3445.415 534.9716) 
(list 3445.415 534.7946) 
(list 3519.4375 535.4446)))
(apply 'command (append '("pline") coords '("c")))
(setq currobj (ssadd (entlast) currobj))
(setq coords (list 
(list 3519.4375 535.3016) 
(list 3445.415 534.6516) 
(list 3445.415 534.4746) 
(list 3519.4375 535.2246)))
(apply 'command (append '("pline") coords '("c")))
(setq currobj (ssadd (entlast) currobj))
(command "_layer" "set" "nitride" "")
(command "_layer" "set" "text" "")
(command "_circle" "3519.0625,524.0816" "0.075")
(command "_circle" "3519.0625,524.3816" "0.075")
(command "_circle" "3519.0625,524.6816" "0.075")
(command "_circle" "3519.0625,524.9816" "0.075")
(command "_circle" "3519.0625,525.2816" "0.075")
(command "_circle" "3518.7625,524.0816" "0.075")
(command "_circle" "3518.7625,524.3816" "0.075")
(command "_circle" "3518.7625,524.6816" "0.075")
(command "_circle" "3518.7625,524.9816" "0.075")
(command "_circle" "3518.7625,525.2816" "0.075")
(command "_circle" "3518.4625,524.0816" "0.075")
(command "_circle" "3518.4625,524.3816" "0.075")
(command "_circle" "3518.4625,524.6816" "0.075")
(command "_circle" "3518.4625,524.9816" "0.075")
(command "_circle" "3518.4625,525.2816" "0.075")
(command "_circle" "3518.1625,524.0816" "0.075")
(command "_circle" "3518.1625,524.3816" "0.075")
(command "_circle" "3518.1625,524.6816" "0.075")
(command "_circle" "3518.1625,524.9816" "0.075")
(command "_circle" "3518.1625,525.2816" "0.075")
(command "_circle" "3517.8625,524.0816" "0.075")
(command "_circle" "3517.8625,524.3816" "0.075")
(command "_circle" "3517.8625,524.6816" "0.075")
(command "_circle" "3517.8625,524.9816" "0.075")
(command "_circle" "3517.8625,525.2816" "0.075")
(command "_layer" "set" "nitride" "")
(setq coords (list 
(list 3520.2625 549.5246) 
(list 3520.2625 665.1693) 
(list 3519.7375 665.1693) 
(list 3519.7375 549.5246)))
(apply 'command (append '("pline") coords '("c")))
(setq currobj (ssadd (entlast) currobj))
(command "_layer" "set" "prebias" "")
(command "_rectangle" "3519.7375,549.5246" "3520.2625,665.1693")
(setq currobj (ssadd (entlast) currobj))
(command "_layer" "set" "nitride" "")
(setq coords (list 
(list 3520.2625 665.1693) 
(list 3520.5625 675.1693) 
(list 3520.5625 675.1693) 
(list 3520.5625 676.1693) 
(list 3594.585 675.4193) 
(list 3594.585 680.3623) 
(list 3520.5625 679.6123) 
(list 3520.5625 680.6123) 
(list 3520.5625 680.6123) 
(list 3520.2625 690.6123) 
(list 3519.7375 690.6123) 
(list 3519.4375 680.6123) 
(list 3519.4375 680.6123) 
(list 3519.4375 679.6123) 
(list 3445.415 680.3623) 
(list 3445.415 675.4193) 
(list 3519.4375 676.1693) 
(list 3519.4375 675.1693) 
(list 3519.4375 675.1693) 
(list 3519.7375 665.1693)))
(apply 'command (append '("pline") coords '("c")))
(setq currobj (ssadd (entlast) currobj))
(command "_layer" "set" "prebias" "")
(setq coords (list 
(list 3519.4375 665.1693) 
(list 3519.4375 676.1693) 
(list 3445.415 675.4193) 
(list 3445.415 680.3623) 
(list 3519.4375 679.6123) 
(list 3519.4375 690.6123) 
(list 3520.5625 690.6123) 
(list 3520.5625 679.6123) 
(list 3594.585 680.3623) 
(list 3594.585 675.4193) 
(list 3520.5625 676.1693) 
(list 3520.5625 665.1693)))
(apply 'command (append '("pline") coords '("c")))
(setq currobj (ssadd (entlast) currobj))
(command "_layer" "set" "nitride" "")
(command "_layer" "set" "fda1" "")
(setq coords (list 
(list 3520.5625 676.3123) 
(list 3594.585 675.5623) 
(list 3594.585 675.7393) 
(list 3520.5625 676.3893)))
(apply 'command (append '("pline") coords '("c")))
(setq currobj (ssadd (entlast) currobj))
(setq coords (list 
(list 3520.5625 676.5323) 
(list 3594.585 675.8823) 
(list 3594.585 676.0593) 
(list 3520.5625 676.6093)))
(apply 'command (append '("pline") coords '("c")))
(setq currobj (ssadd (entlast) currobj))
(setq coords (list 
(list 3520.5625 676.7523) 
(list 3594.585 676.2023) 
(list 3594.585 676.3793) 
(list 3520.5625 676.8293)))
(apply 'command (append '("pline") coords '("c")))
(setq currobj (ssadd (entlast) currobj))
(setq coords (list 
(list 3520.5625 676.9723) 
(list 3594.585 676.5223) 
(list 3594.585 676.6993) 
(list 3520.5625 677.0493)))
(apply 'command (append '("pline") coords '("c")))
(setq currobj (ssadd (entlast) currobj))
(setq coords (list 
(list 3520.5625 677.1923) 
(list 3594.585 676.8423) 
(list 3594.585 677.0193) 
(list 3520.5625 677.2693)))
(apply 'command (append '("pline") coords '("c")))
(setq currobj (ssadd (entlast) currobj))
(setq coords (list 
(list 3520.5625 677.4123) 
(list 3594.585 677.1623) 
(list 3594.585 677.3393) 
(list 3520.5625 677.4893)))
(apply 'command (append '("pline") coords '("c")))
(setq currobj (ssadd (entlast) currobj))
(setq coords (list 
(list 3520.5625 677.6323) 
(list 3594.585 677.4823) 
(list 3594.585 677.6593) 
(list 3520.5625 677.7093)))
(apply 'command (append '("pline") coords '("c")))
(setq currobj (ssadd (entlast) currobj))
(setq coords (list 
(list 3520.5625 677.8523) 
(list 3594.585 677.8023) 
(list 3594.585 677.9793) 
(list 3520.5625 677.9293)))
(apply 'command (append '("pline") coords '("c")))
(setq currobj (ssadd (entlast) currobj))
(setq coords (list 
(list 3520.5625 678.0723) 
(list 3594.585 678.1223) 
(list 3594.585 678.2993) 
(list 3520.5625 678.1493)))
(apply 'command (append '("pline") coords '("c")))
(setq currobj (ssadd (entlast) currobj))
(setq coords (list 
(list 3520.5625 678.2923) 
(list 3594.585 678.4423) 
(list 3594.585 678.6193) 
(list 3520.5625 678.3693)))
(apply 'command (append '("pline") coords '("c")))
(setq currobj (ssadd (entlast) currobj))
(setq coords (list 
(list 3520.5625 678.5123) 
(list 3594.585 678.7623) 
(list 3594.585 678.9393) 
(list 3520.5625 678.5893)))
(apply 'command (append '("pline") coords '("c")))
(setq currobj (ssadd (entlast) currobj))
(setq coords (list 
(list 3520.5625 678.7323) 
(list 3594.585 679.0823) 
(list 3594.585 679.2593) 
(list 3520.5625 678.8093)))
(apply 'command (append '("pline") coords '("c")))
(setq currobj (ssadd (entlast) currobj))
(setq coords (list 
(list 3520.5625 678.9523) 
(list 3594.585 679.4023) 
(list 3594.585 679.5793) 
(list 3520.5625 679.0293)))
(apply 'command (append '("pline") coords '("c")))
(setq currobj (ssadd (entlast) currobj))
(setq coords (list 
(list 3520.5625 679.1723) 
(list 3594.585 679.7223) 
(list 3594.585 679.8993) 
(list 3520.5625 679.2493)))
(apply 'command (append '("pline") coords '("c")))
(setq currobj (ssadd (entlast) currobj))
(setq coords (list 
(list 3520.5625 679.3923) 
(list 3594.585 680.0423) 
(list 3594.585 680.2193) 
(list 3520.5625 679.4693)))
(apply 'command (append '("pline") coords '("c")))
(setq currobj (ssadd (entlast) currobj))
(setq coords (list 
(list 3519.4375 679.4693) 
(list 3445.415 680.2193) 
(list 3445.415 680.0423) 
(list 3519.4375 679.3923)))
(apply 'command (append '("pline") coords '("c")))
(setq currobj (ssadd (entlast) currobj))
(setq coords (list 
(list 3519.4375 679.2493) 
(list 3445.415 679.8993) 
(list 3445.415 679.7223) 
(list 3519.4375 679.1723)))
(apply 'command (append '("pline") coords '("c")))
(setq currobj (ssadd (entlast) currobj))
(setq coords (list 
(list 3519.4375 679.0293) 
(list 3445.415 679.5793) 
(list 3445.415 679.4023) 
(list 3519.4375 678.9523)))
(apply 'command (append '("pline") coords '("c")))
(setq currobj (ssadd (entlast) currobj))
(setq coords (list 
(list 3519.4375 678.8093) 
(list 3445.415 679.2593) 
(list 3445.415 679.0823) 
(list 3519.4375 678.7323)))
(apply 'command (append '("pline") coords '("c")))
(setq currobj (ssadd (entlast) currobj))
(setq coords (list 
(list 3519.4375 678.5893) 
(list 3445.415 678.9393) 
(list 3445.415 678.7623) 
(list 3519.4375 678.5123)))
(apply 'command (append '("pline") coords '("c")))
(setq currobj (ssadd (entlast) currobj))
(setq coords (list 
(list 3519.4375 678.3693) 
(list 3445.415 678.6193) 
(list 3445.415 678.4423) 
(list 3519.4375 678.2923)))
(apply 'command (append '("pline") coords '("c")))
(setq currobj (ssadd (entlast) currobj))
(setq coords (list 
(list 3519.4375 678.1493) 
(list 3445.415 678.2993) 
(list 3445.415 678.1223) 
(list 3519.4375 678.0723)))
(apply 'command (append '("pline") coords '("c")))
(setq currobj (ssadd (entlast) currobj))
(setq coords (list 
(list 3519.4375 677.9293) 
(list 3445.415 677.9793) 
(list 3445.415 677.8023) 
(list 3519.4375 677.8523)))
(apply 'command (append '("pline") coords '("c")))
(setq currobj (ssadd (entlast) currobj))
(setq coords (list 
(list 3519.4375 677.7093) 
(list 3445.415 677.6593) 
(list 3445.415 677.4823) 
(list 3519.4375 677.6323)))
(apply 'command (append '("pline") coords '("c")))
(setq currobj (ssadd (entlast) currobj))
(setq coords (list 
(list 3519.4375 677.4893) 
(list 3445.415 677.3393) 
(list 3445.415 677.1623) 
(list 3519.4375 677.4123)))
(apply 'command (append '("pline") coords '("c")))
(setq currobj (ssadd (entlast) currobj))
(setq coords (list 
(list 3519.4375 677.2693) 
(list 3445.415 677.0193) 
(list 3445.415 676.8423) 
(list 3519.4375 677.1923)))
(apply 'command (append '("pline") coords '("c")))
(setq currobj (ssadd (entlast) currobj))
(setq coords (list 
(list 3519.4375 677.0493) 
(list 3445.415 676.6993) 
(list 3445.415 676.5223) 
(list 3519.4375 676.9723)))
(apply 'command (append '("pline") coords '("c")))
(setq currobj (ssadd (entlast) currobj))
(setq coords (list 
(list 3519.4375 676.8293) 
(list 3445.415 676.3793) 
(list 3445.415 676.2023) 
(list 3519.4375 676.7523)))
(apply 'command (append '("pline") coords '("c")))
(setq currobj (ssadd (entlast) currobj))
(setq coords (list 
(list 3519.4375 676.6093) 
(list 3445.415 676.0593) 
(list 3445.415 675.8823) 
(list 3519.4375 676.5323)))
(apply 'command (append '("pline") coords '("c")))
(setq currobj (ssadd (entlast) currobj))
(setq coords (list 
(list 3519.4375 676.3893) 
(list 3445.415 675.7393) 
(list 3445.415 675.5623) 
(list 3519.4375 676.3123)))
(apply 'command (append '("pline") coords '("c")))
(setq currobj (ssadd (entlast) currobj))
(command "_layer" "set" "nitride" "")
(command "_layer" "set" "text" "")
(command "_circle" "3519.0625,665.1693" "0.075")
(command "_circle" "3519.0625,665.4693" "0.075")
(command "_circle" "3519.0625,665.7693" "0.075")
(command "_circle" "3519.0625,666.0693" "0.075")
(command "_circle" "3519.0625,666.3693" "0.075")
(command "_circle" "3518.7625,665.1693" "0.075")
(command "_circle" "3518.7625,665.4693" "0.075")
(command "_circle" "3518.7625,665.7693" "0.075")
(command "_circle" "3518.7625,666.0693" "0.075")
(command "_circle" "3518.7625,666.3693" "0.075")
(command "_circle" "3518.4625,665.1693" "0.075")
(command "_circle" "3518.4625,665.4693" "0.075")
(command "_circle" "3518.4625,665.7693" "0.075")
(command "_circle" "3518.4625,666.0693" "0.075")
(command "_circle" "3518.4625,666.3693" "0.075")
(command "_circle" "3518.1625,665.1693" "0.075")
(command "_circle" "3518.1625,665.4693" "0.075")
(command "_circle" "3518.1625,665.7693" "0.075")
(command "_circle" "3518.1625,666.0693" "0.075")
(command "_circle" "3518.1625,666.3693" "0.075")
(command "_circle" "3517.8625,665.1693" "0.075")
(command "_circle" "3517.8625,665.4693" "0.075")
(command "_circle" "3517.8625,665.7693" "0.075")
(command "_circle" "3517.8625,666.0693" "0.075")
(command "_circle" "3517.8625,666.3693" "0.075")
(command "_layer" "set" "nitride" "")
(setq coords (list 
(list 3520.2625 690.6123) 
(list 3520.2625 806.257) 
(list 3519.7375 806.257) 
(list 3519.7375 690.6123)))
(apply 'command (append '("pline") coords '("c")))
(setq currobj (ssadd (entlast) currobj))
(command "_layer" "set" "prebias" "")
(command "_rectangle" "3519.7375,690.6123" "3520.2625,806.257")
(setq currobj (ssadd (entlast) currobj))
(command "_layer" "set" "nitride" "")
(setq coords (list 
(list 3520.2625 806.257) 
(list 3520.5625 816.257) 
(list 3520.5625 816.257) 
(list 3520.5625 817.257) 
(list 3594.585 816.507) 
(list 3594.585 821.45) 
(list 3520.5625 820.7) 
(list 3520.5625 821.7) 
(list 3520.5625 821.7) 
(list 3520.2625 831.7) 
(list 3519.7375 831.7) 
(list 3519.4375 821.7) 
(list 3519.4375 821.7) 
(list 3519.4375 820.7) 
(list 3445.415 821.45) 
(list 3445.415 816.507) 
(list 3519.4375 817.257) 
(list 3519.4375 816.257) 
(list 3519.4375 816.257) 
(list 3519.7375 806.257)))
(apply 'command (append '("pline") coords '("c")))
(setq currobj (ssadd (entlast) currobj))
(command "_layer" "set" "prebias" "")
(setq coords (list 
(list 3519.4375 806.257) 
(list 3519.4375 817.257) 
(list 3445.415 816.507) 
(list 3445.415 821.45) 
(list 3519.4375 820.7) 
(list 3519.4375 831.7) 
(list 3520.5625 831.7) 
(list 3520.5625 820.7) 
(list 3594.585 821.45) 
(list 3594.585 816.507) 
(list 3520.5625 817.257) 
(list 3520.5625 806.257)))
(apply 'command (append '("pline") coords '("c")))
(setq currobj (ssadd (entlast) currobj))
(command "_layer" "set" "nitride" "")
(command "_layer" "set" "fda1" "")
(setq coords (list 
(list 3520.5625 817.4) 
(list 3594.585 816.65) 
(list 3594.585 816.827) 
(list 3520.5625 817.477)))
(apply 'command (append '("pline") coords '("c")))
(setq currobj (ssadd (entlast) currobj))
(setq coords (list 
(list 3520.5625 817.62) 
(list 3594.585 816.97) 
(list 3594.585 817.147) 
(list 3520.5625 817.697)))
(apply 'command (append '("pline") coords '("c")))
(setq currobj (ssadd (entlast) currobj))
(setq coords (list 
(list 3520.5625 817.84) 
(list 3594.585 817.29) 
(list 3594.585 817.467) 
(list 3520.5625 817.917)))
(apply 'command (append '("pline") coords '("c")))
(setq currobj (ssadd (entlast) currobj))
(setq coords (list 
(list 3520.5625 818.06) 
(list 3594.585 817.61) 
(list 3594.585 817.787) 
(list 3520.5625 818.137)))
(apply 'command (append '("pline") coords '("c")))
(setq currobj (ssadd (entlast) currobj))
(setq coords (list 
(list 3520.5625 818.28) 
(list 3594.585 817.93) 
(list 3594.585 818.107) 
(list 3520.5625 818.357)))
(apply 'command (append '("pline") coords '("c")))
(setq currobj (ssadd (entlast) currobj))
(setq coords (list 
(list 3520.5625 818.5) 
(list 3594.585 818.25) 
(list 3594.585 818.427) 
(list 3520.5625 818.577)))
(apply 'command (append '("pline") coords '("c")))
(setq currobj (ssadd (entlast) currobj))
(setq coords (list 
(list 3520.5625 818.72) 
(list 3594.585 818.57) 
(list 3594.585 818.747) 
(list 3520.5625 818.797)))
(apply 'command (append '("pline") coords '("c")))
(setq currobj (ssadd (entlast) currobj))
(setq coords (list 
(list 3520.5625 818.94) 
(list 3594.585 818.89) 
(list 3594.585 819.067) 
(list 3520.5625 819.017)))
(apply 'command (append '("pline") coords '("c")))
(setq currobj (ssadd (entlast) currobj))
(setq coords (list 
(list 3520.5625 819.16) 
(list 3594.585 819.21) 
(list 3594.585 819.387) 
(list 3520.5625 819.237)))
(apply 'command (append '("pline") coords '("c")))
(setq currobj (ssadd (entlast) currobj))
(setq coords (list 
(list 3520.5625 819.38) 
(list 3594.585 819.53) 
(list 3594.585 819.707) 
(list 3520.5625 819.457)))
(apply 'command (append '("pline") coords '("c")))
(setq currobj (ssadd (entlast) currobj))
(setq coords (list 
(list 3520.5625 819.6) 
(list 3594.585 819.85) 
(list 3594.585 820.027) 
(list 3520.5625 819.677)))
(apply 'command (append '("pline") coords '("c")))
(setq currobj (ssadd (entlast) currobj))
(setq coords (list 
(list 3520.5625 819.82) 
(list 3594.585 820.17) 
(list 3594.585 820.347) 
(list 3520.5625 819.897)))
(apply 'command (append '("pline") coords '("c")))
(setq currobj (ssadd (entlast) currobj))
(setq coords (list 
(list 3520.5625 820.04) 
(list 3594.585 820.49) 
(list 3594.585 820.667) 
(list 3520.5625 820.117)))
(apply 'command (append '("pline") coords '("c")))
(setq currobj (ssadd (entlast) currobj))
(setq coords (list 
(list 3520.5625 820.26) 
(list 3594.585 820.81) 
(list 3594.585 820.987) 
(list 3520.5625 820.337)))
(apply 'command (append '("pline") coords '("c")))
(setq currobj (ssadd (entlast) currobj))
(setq coords (list 
(list 3520.5625 820.48) 
(list 3594.585 821.13) 
(list 3594.585 821.307) 
(list 3520.5625 820.557)))
(apply 'command (append '("pline") coords '("c")))
(setq currobj (ssadd (entlast) currobj))
(setq coords (list 
(list 3519.4375 820.557) 
(list 3445.415 821.307) 
(list 3445.415 821.13) 
(list 3519.4375 820.48)))
(apply 'command (append '("pline") coords '("c")))
(setq currobj (ssadd (entlast) currobj))
(setq coords (list 
(list 3519.4375 820.337) 
(list 3445.415 820.987) 
(list 3445.415 820.81) 
(list 3519.4375 820.26)))
(apply 'command (append '("pline") coords '("c")))
(setq currobj (ssadd (entlast) currobj))
(setq coords (list 
(list 3519.4375 820.117) 
(list 3445.415 820.667) 
(list 3445.415 820.49) 
(list 3519.4375 820.04)))
(apply 'command (append '("pline") coords '("c")))
(setq currobj (ssadd (entlast) currobj))
(setq coords (list 
(list 3519.4375 819.897) 
(list 3445.415 820.347) 
(list 3445.415 820.17) 
(list 3519.4375 819.82)))
(apply 'command (append '("pline") coords '("c")))
(setq currobj (ssadd (entlast) currobj))
(setq coords (list 
(list 3519.4375 819.677) 
(list 3445.415 820.027) 
(list 3445.415 819.85) 
(list 3519.4375 819.6)))
(apply 'command (append '("pline") coords '("c")))
(setq currobj (ssadd (entlast) currobj))
(setq coords (list 
(list 3519.4375 819.457) 
(list 3445.415 819.707) 
(list 3445.415 819.53) 
(list 3519.4375 819.38)))
(apply 'command (append '("pline") coords '("c")))
(setq currobj (ssadd (entlast) currobj))
(setq coords (list 
(list 3519.4375 819.237) 
(list 3445.415 819.387) 
(list 3445.415 819.21) 
(list 3519.4375 819.16)))
(apply 'command (append '("pline") coords '("c")))
(setq currobj (ssadd (entlast) currobj))
(setq coords (list 
(list 3519.4375 819.017) 
(list 3445.415 819.067) 
(list 3445.415 818.89) 
(list 3519.4375 818.94)))
(apply 'command (append '("pline") coords '("c")))
(setq currobj (ssadd (entlast) currobj))
(setq coords (list 
(list 3519.4375 818.797) 
(list 3445.415 818.747) 
(list 3445.415 818.57) 
(list 3519.4375 818.72)))
(apply 'command (append '("pline") coords '("c")))
(setq currobj (ssadd (entlast) currobj))
(setq coords (list 
(list 3519.4375 818.577) 
(list 3445.415 818.427) 
(list 3445.415 818.25) 
(list 3519.4375 818.5)))
(apply 'command (append '("pline") coords '("c")))
(setq currobj (ssadd (entlast) currobj))
(setq coords (list 
(list 3519.4375 818.357) 
(list 3445.415 818.107) 
(list 3445.415 817.93) 
(list 3519.4375 818.28)))
(apply 'command (append '("pline") coords '("c")))
(setq currobj (ssadd (entlast) currobj))
(setq coords (list 
(list 3519.4375 818.137) 
(list 3445.415 817.787) 
(list 3445.415 817.61) 
(list 3519.4375 818.06)))
(apply 'command (append '("pline") coords '("c")))
(setq currobj (ssadd (entlast) currobj))
(setq coords (list 
(list 3519.4375 817.917) 
(list 3445.415 817.467) 
(list 3445.415 817.29) 
(list 3519.4375 817.84)))
(apply 'command (append '("pline") coords '("c")))
(setq currobj (ssadd (entlast) currobj))
(setq coords (list 
(list 3519.4375 817.697) 
(list 3445.415 817.147) 
(list 3445.415 816.97) 
(list 3519.4375 817.62)))
(apply 'command (append '("pline") coords '("c")))
(setq currobj (ssadd (entlast) currobj))
(setq coords (list 
(list 3519.4375 817.477) 
(list 3445.415 816.827) 
(list 3445.415 816.65) 
(list 3519.4375 817.4)))
(apply 'command (append '("pline") coords '("c")))
(setq currobj (ssadd (entlast) currobj))
(command "_layer" "set" "nitride" "")
(command "_layer" "set" "text" "")
(command "_circle" "3519.0625,806.257" "0.075")
(command "_circle" "3519.0625,806.557" "0.075")
(command "_circle" "3519.0625,806.857" "0.075")
(command "_circle" "3519.0625,807.157" "0.075")
(command "_circle" "3519.0625,807.457" "0.075")
(command "_circle" "3518.7625,806.257" "0.075")
(command "_circle" "3518.7625,806.557" "0.075")
(command "_circle" "3518.7625,806.857" "0.075")
(command "_circle" "3518.7625,807.157" "0.075")
(command "_circle" "3518.7625,807.457" "0.075")
(command "_circle" "3518.4625,806.257" "0.075")
(command "_circle" "3518.4625,806.557" "0.075")
(command "_circle" "3518.4625,806.857" "0.075")
(command "_circle" "3518.4625,807.157" "0.075")
(command "_circle" "3518.4625,807.457" "0.075")
(command "_circle" "3518.1625,806.257" "0.075")
(command "_circle" "3518.1625,806.557" "0.075")
(command "_circle" "3518.1625,806.857" "0.075")
(command "_circle" "3518.1625,807.157" "0.075")
(command "_circle" "3518.1625,807.457" "0.075")
(command "_circle" "3517.8625,806.257" "0.075")
(command "_circle" "3517.8625,806.557" "0.075")
(command "_circle" "3517.8625,806.857" "0.075")
(command "_circle" "3517.8625,807.157" "0.075")
(command "_circle" "3517.8625,807.457" "0.075")
(command "_layer" "set" "nitride" "")
(setq coords (list 
(list 3520.2625 831.7) 
(list 3520.2625 836.7) 
(list 3519.7375 836.7) 
(list 3519.7375 831.7)))
(apply 'command (append '("pline") coords '("c")))
(setq currobj (ssadd (entlast) currobj))
(command "_layer" "set" "prebias" "")
(command "_rectangle" "3519.7375,831.7" "3520.2625,836.7")
(setq currobj (ssadd (entlast) currobj))
(command "_layer" "set" "nitride" "")
(setq cooledsinglenanobeam11 currobj)
(setq currobj nil)
(setq currobj (ssadd))
; DRAWING PHOTONIC CRYSTAL
(command "_layer" "set" "negYjunc" "")
(setq coords (list 
(list 3520.135 866.7) 
(list 3520 851.7) 
(list 3520 866.7)))
(apply 'command (append '("pline") coords '("c")))
(setq currobj (ssadd (entlast) currobj))
(setq coords (list 
(list 3520.2625 836.7) 
(list 3520.415 866.7) 
(list 3521.132 866.7) 
(list 3521.132 836.7)))
(apply 'command (append '("pline") coords '("c")))
(setq currobj (ssadd (entlast) currobj))
(setq coords (list 
(list 3519.865 866.7) 
(list 3520 851.7) 
(list 3520 866.7)))
(apply 'command (append '("pline") coords '("c")))
(setq currobj (ssadd (entlast) currobj))
(setq coords (list 
(list 3519.7375 836.7) 
(list 3519.585 866.7) 
(list 3518.868 866.7) 
(list 3518.868 836.7)))
(apply 'command (append '("pline") coords '("c")))
(setq currobj (ssadd (entlast) currobj))
(command "_layer" "set" "nitride" "")
(setq yjunction11 currobj)
(setq currobj nil)
(setq currobj (ssadd))
(setq tap11 nil)
(setq tap11 (ssadd))
(command "_layer" "set" "phc" "")
(setq coords (list 
(list 3520 866.7) 
(list 3520.135 866.7) 
(list 3520.135 866.7103) 
(list 3520.135 866.7206) 
(list 3520.135 866.7308) 
(list 3520.135 866.7411) 
(list 3520.135 866.7514) 
(list 3520.135 866.7617) 
(list 3520.135 866.7719) 
(list 3520.135 866.7822) 
(list 3520.135 866.7925) 
(list 3520.135 866.8028) 
(list 3520.135 866.8131) 
(list 3520.135 866.8233) 
(list 3520.135 866.8336) 
(list 3520.135 866.8439) 
(list 3520.135 866.8542) 
(list 3520.135 866.8644) 
(list 3520.135 866.8747) 
(list 3520.135 866.885) 
(list 3520.135 866.8953) 
(list 3520.135 866.9056) 
(list 3520.135 866.9158) 
(list 3520.135 866.9261) 
(list 3520.135 866.9364) 
(list 3520.135 866.9467) 
(list 3520.135 866.9569) 
(list 3520.135 866.9672) 
(list 3520.135 866.9775) 
(list 3520.135 866.9878) 
(list 3520.135 866.9981) 
(list 3520.135 867.0083) 
(list 3520.135 867.0186) 
(list 3520.135 867.0289) 
(list 3520.135 867.0392) 
(list 3520.135 867.0494) 
(list 3520.135 867.0597) 
(list 3520.135 867.07) 
(list 3520 867.07)))
(apply 'command (append '("pline") coords '("c")))
(setq tap11 (ssadd (entlast) tap11))
(command "_mirror" (entlast) "" "3520,900" "3520,901" "No")
(setq tap11 (ssadd (entlast) tap11))
(setq coords (list 
(list 3520.4251 866.7) 
(list 3520.415 866.7) 
(list 3520.4153 866.7103) 
(list 3520.4155 866.7206) 
(list 3520.4157 866.7308) 
(list 3520.4159 866.7411) 
(list 3520.416 866.7514) 
(list 3520.4159 866.7617) 
(list 3520.4158 866.7719) 
(list 3520.4156 866.7822) 
(list 3520.4153 866.7925) 
(list 3520.4149 866.8028) 
(list 3520.4144 866.8131) 
(list 3520.4139 866.8233) 
(list 3520.4133 866.8336) 
(list 3520.4127 866.8439) 
(list 3520.4122 866.8542) 
(list 3520.4117 866.8644) 
(list 3520.4113 866.8747) 
(list 3520.411 866.885) 
(list 3520.4109 866.8953) 
(list 3520.4109 866.9056) 
(list 3520.4111 866.9158) 
(list 3520.4114 866.9261) 
(list 3520.412 866.9364) 
(list 3520.4127 866.9467) 
(list 3520.4136 866.9569) 
(list 3520.4146 866.9672) 
(list 3520.4158 866.9775) 
(list 3520.417 866.9878) 
(list 3520.4183 866.9981) 
(list 3520.4196 867.0083) 
(list 3520.4209 867.0186) 
(list 3520.4221 867.0289) 
(list 3520.4231 867.0392) 
(list 3520.424 867.0494) 
(list 3520.4247 867.0597) 
(list 3520.4251 867.07) 
(list 3520.4251 867.07)))
(apply 'command (append '("pline") coords '("c")))
(setq tap11 (ssadd (entlast) tap11))
(command "_mirror" (entlast) "" "3520,900" "3520,901" "No")
(setq tap11 (ssadd (entlast) tap11))
(setq coords (list 
(list 3521.132 866.7) 
(list 3520.4251 866.7) 
(list 3520.4251 866.7103) 
(list 3520.4251 866.7206) 
(list 3520.4251 866.7308) 
(list 3520.4251 866.7411) 
(list 3520.4251 866.7514) 
(list 3520.4251 866.7617) 
(list 3520.4251 866.7719) 
(list 3520.4251 866.7822) 
(list 3520.4251 866.7925) 
(list 3520.4251 866.8028) 
(list 3520.4251 866.8131) 
(list 3520.4251 866.8233) 
(list 3520.4251 866.8336) 
(list 3520.4251 866.8439) 
(list 3520.4251 866.8542) 
(list 3520.4251 866.8644) 
(list 3520.4251 866.8747) 
(list 3520.4251 866.885) 
(list 3520.4251 866.8953) 
(list 3520.4251 866.9056) 
(list 3520.4251 866.9158) 
(list 3520.4251 866.9261) 
(list 3520.4251 866.9364) 
(list 3520.4251 866.9467) 
(list 3520.4251 866.9569) 
(list 3520.4251 866.9672) 
(list 3520.4251 866.9775) 
(list 3520.4251 866.9878) 
(list 3520.4251 866.9981) 
(list 3520.4251 867.0083) 
(list 3520.4251 867.0186) 
(list 3520.4251 867.0289) 
(list 3520.4251 867.0392) 
(list 3520.4251 867.0494) 
(list 3520.4251 867.0597) 
(list 3520.4251 867.07) 
(list 3521.132 867.07)))
(apply 'command (append '("pline") coords '("c")))
(setq tap11 (ssadd (entlast) tap11))
(command "_mirror" (entlast) "" "3520,900" "3520,901" "No")
(setq tap11 (ssadd (entlast) tap11))
(setq coords (list 
(list 3520 867.07) 
(list 3520.135 867.07) 
(list 3520.135 867.0803) 
(list 3520.135 867.0906) 
(list 3520.135 867.1008) 
(list 3520.135 867.1111) 
(list 3520.135 867.1214) 
(list 3520.135 867.1317) 
(list 3520.135 867.1419) 
(list 3520.135 867.1522) 
(list 3520.135 867.1625) 
(list 3520.135 867.1728) 
(list 3520.135 867.1831) 
(list 3520.135 867.1933) 
(list 3520.135 867.2036) 
(list 3520.135 867.2139) 
(list 3520.135 867.2242) 
(list 3520.135 867.2344) 
(list 3520.135 867.2447) 
(list 3520.135 867.255) 
(list 3520.135 867.2653) 
(list 3520.135 867.2756) 
(list 3520.135 867.2858) 
(list 3520.135 867.2961) 
(list 3520.135 867.3064) 
(list 3520.135 867.3167) 
(list 3520.135 867.3269) 
(list 3520.135 867.3372) 
(list 3520.135 867.3475) 
(list 3520.135 867.3578) 
(list 3520.135 867.3681) 
(list 3520.135 867.3783) 
(list 3520.135 867.3886) 
(list 3520.135 867.3989) 
(list 3520.135 867.4092) 
(list 3520.135 867.4194) 
(list 3520.135 867.4297) 
(list 3520.135 867.44) 
(list 3520 867.44)))
(apply 'command (append '("pline") coords '("c")))
(setq tap11 (ssadd (entlast) tap11))
(command "_mirror" (entlast) "" "3520,900" "3520,901" "No")
(setq tap11 (ssadd (entlast) tap11))
(setq coords (list 
(list 3520.4351 867.07) 
(list 3520.4251 867.07) 
(list 3520.4252 867.0803) 
(list 3520.4251 867.0906) 
(list 3520.4246 867.1008) 
(list 3520.4238 867.1111) 
(list 3520.4228 867.1214) 
(list 3520.4215 867.1317) 
(list 3520.42 867.1419) 
(list 3520.4182 867.1522) 
(list 3520.4163 867.1625) 
(list 3520.4144 867.1728) 
(list 3520.4124 867.1831) 
(list 3520.4104 867.1933) 
(list 3520.4086 867.2036) 
(list 3520.4069 867.2139) 
(list 3520.4055 867.2242) 
(list 3520.4043 867.2344) 
(list 3520.4035 867.2447) 
(list 3520.4031 867.255) 
(list 3520.4031 867.2653) 
(list 3520.4035 867.2756) 
(list 3520.4043 867.2858) 
(list 3520.4056 867.2961) 
(list 3520.4073 867.3064) 
(list 3520.4093 867.3167) 
(list 3520.4116 867.3269) 
(list 3520.4141 867.3372) 
(list 3520.4169 867.3475) 
(list 3520.4197 867.3578) 
(list 3520.4225 867.3681) 
(list 3520.4252 867.3783) 
(list 3520.4278 867.3886) 
(list 3520.43 867.3989) 
(list 3520.432 867.4092) 
(list 3520.4335 867.4194) 
(list 3520.4346 867.4297) 
(list 3520.4351 867.44) 
(list 3520.4351 867.44)))
(apply 'command (append '("pline") coords '("c")))
(setq tap11 (ssadd (entlast) tap11))
(command "_mirror" (entlast) "" "3520,900" "3520,901" "No")
(setq tap11 (ssadd (entlast) tap11))
(setq coords (list 
(list 3521.132 867.07) 
(list 3520.4351 867.07) 
(list 3520.4351 867.0803) 
(list 3520.4351 867.0906) 
(list 3520.4351 867.1008) 
(list 3520.4351 867.1111) 
(list 3520.4351 867.1214) 
(list 3520.4351 867.1317) 
(list 3520.4351 867.1419) 
(list 3520.4351 867.1522) 
(list 3520.4351 867.1625) 
(list 3520.4351 867.1728) 
(list 3520.4351 867.1831) 
(list 3520.4351 867.1933) 
(list 3520.4351 867.2036) 
(list 3520.4351 867.2139) 
(list 3520.4351 867.2242) 
(list 3520.4351 867.2344) 
(list 3520.4351 867.2447) 
(list 3520.4351 867.255) 
(list 3520.4351 867.2653) 
(list 3520.4351 867.2756) 
(list 3520.4351 867.2858) 
(list 3520.4351 867.2961) 
(list 3520.4351 867.3064) 
(list 3520.4351 867.3167) 
(list 3520.4351 867.3269) 
(list 3520.4351 867.3372) 
(list 3520.4351 867.3475) 
(list 3520.4351 867.3578) 
(list 3520.4351 867.3681) 
(list 3520.4351 867.3783) 
(list 3520.4351 867.3886) 
(list 3520.4351 867.3989) 
(list 3520.4351 867.4092) 
(list 3520.4351 867.4194) 
(list 3520.4351 867.4297) 
(list 3520.4351 867.44) 
(list 3521.132 867.44)))
(apply 'command (append '("pline") coords '("c")))
(setq tap11 (ssadd (entlast) tap11))
(command "_mirror" (entlast) "" "3520,900" "3520,901" "No")
(setq tap11 (ssadd (entlast) tap11))
(setq coords (list 
(list 3520 867.44) 
(list 3520.135 867.44) 
(list 3520.135 867.4503) 
(list 3520.135 867.4606) 
(list 3520.135 867.4708) 
(list 3520.135 867.4811) 
(list 3520.135 867.4914) 
(list 3520.135 867.5017) 
(list 3520.135 867.5119) 
(list 3520.135 867.5222) 
(list 3520.135 867.5325) 
(list 3520.135 867.5428) 
(list 3520.135 867.5531) 
(list 3520.135 867.5633) 
(list 3520.135 867.5736) 
(list 3520.135 867.5839) 
(list 3520.135 867.5942) 
(list 3520.135 867.6044) 
(list 3520.135 867.6147) 
(list 3520.135 867.625) 
(list 3520.135 867.6353) 
(list 3520.135 867.6456) 
(list 3520.135 867.6558) 
(list 3520.135 867.6661) 
(list 3520.135 867.6764) 
(list 3520.135 867.6867) 
(list 3520.135 867.6969) 
(list 3520.135 867.7072) 
(list 3520.135 867.7175) 
(list 3520.135 867.7278) 
(list 3520.135 867.7381) 
(list 3520.135 867.7483) 
(list 3520.135 867.7586) 
(list 3520.135 867.7689) 
(list 3520.135 867.7792) 
(list 3520.135 867.7894) 
(list 3520.135 867.7997) 
(list 3520.135 867.81) 
(list 3520 867.81)))
(apply 'command (append '("pline") coords '("c")))
(setq tap11 (ssadd (entlast) tap11))
(command "_mirror" (entlast) "" "3520,900" "3520,901" "No")
(setq tap11 (ssadd (entlast) tap11))
(setq coords (list 
(list 3520.4452 867.44) 
(list 3520.4351 867.44) 
(list 3520.4351 867.4503) 
(list 3520.4346 867.4606) 
(list 3520.4335 867.4708) 
(list 3520.4318 867.4811) 
(list 3520.4297 867.4914) 
(list 3520.4271 867.5017) 
(list 3520.4241 867.5119) 
(list 3520.4208 867.5222) 
(list 3520.4174 867.5325) 
(list 3520.4139 867.5428) 
(list 3520.4104 867.5531) 
(list 3520.407 867.5633) 
(list 3520.4039 867.5736) 
(list 3520.4011 867.5839) 
(list 3520.3987 867.5942) 
(list 3520.3969 867.6044) 
(list 3520.3957 867.6147) 
(list 3520.3952 867.625) 
(list 3520.3953 867.6353) 
(list 3520.3961 867.6456) 
(list 3520.3976 867.6558) 
(list 3520.3998 867.6661) 
(list 3520.4025 867.6764) 
(list 3520.4058 867.6867) 
(list 3520.4096 867.6969) 
(list 3520.4136 867.7072) 
(list 3520.4179 867.7175) 
(list 3520.4223 867.7278) 
(list 3520.4266 867.7381) 
(list 3520.4308 867.7483) 
(list 3520.4346 867.7586) 
(list 3520.438 867.7689) 
(list 3520.4408 867.7792) 
(list 3520.443 867.7894) 
(list 3520.4445 867.7997) 
(list 3520.4452 867.81) 
(list 3520.4452 867.81)))
(apply 'command (append '("pline") coords '("c")))
(setq tap11 (ssadd (entlast) tap11))
(command "_mirror" (entlast) "" "3520,900" "3520,901" "No")
(setq tap11 (ssadd (entlast) tap11))
(setq coords (list 
(list 3521.132 867.44) 
(list 3520.4452 867.44) 
(list 3520.4452 867.4503) 
(list 3520.4452 867.4606) 
(list 3520.4452 867.4708) 
(list 3520.4452 867.4811) 
(list 3520.4452 867.4914) 
(list 3520.4452 867.5017) 
(list 3520.4452 867.5119) 
(list 3520.4452 867.5222) 
(list 3520.4452 867.5325) 
(list 3520.4452 867.5428) 
(list 3520.4452 867.5531) 
(list 3520.4452 867.5633) 
(list 3520.4452 867.5736) 
(list 3520.4452 867.5839) 
(list 3520.4452 867.5942) 
(list 3520.4452 867.6044) 
(list 3520.4452 867.6147) 
(list 3520.4452 867.625) 
(list 3520.4452 867.6353) 
(list 3520.4452 867.6456) 
(list 3520.4452 867.6558) 
(list 3520.4452 867.6661) 
(list 3520.4452 867.6764) 
(list 3520.4452 867.6867) 
(list 3520.4452 867.6969) 
(list 3520.4452 867.7072) 
(list 3520.4452 867.7175) 
(list 3520.4452 867.7278) 
(list 3520.4452 867.7381) 
(list 3520.4452 867.7483) 
(list 3520.4452 867.7586) 
(list 3520.4452 867.7689) 
(list 3520.4452 867.7792) 
(list 3520.4452 867.7894) 
(list 3520.4452 867.7997) 
(list 3520.4452 867.81) 
(list 3521.132 867.81)))
(apply 'command (append '("pline") coords '("c")))
(setq tap11 (ssadd (entlast) tap11))
(command "_mirror" (entlast) "" "3520,900" "3520,901" "No")
(setq tap11 (ssadd (entlast) tap11))
(setq coords (list 
(list 3520 867.81) 
(list 3520.135 867.81) 
(list 3520.135 867.8203) 
(list 3520.135 867.8306) 
(list 3520.135 867.8408) 
(list 3520.135 867.8511) 
(list 3520.135 867.8614) 
(list 3520.135 867.8717) 
(list 3520.135 867.8819) 
(list 3520.135 867.8922) 
(list 3520.135 867.9025) 
(list 3520.135 867.9128) 
(list 3520.135 867.9231) 
(list 3520.135 867.9333) 
(list 3520.135 867.9436) 
(list 3520.135 867.9539) 
(list 3520.135 867.9642) 
(list 3520.135 867.9744) 
(list 3520.135 867.9847) 
(list 3520.135 867.995) 
(list 3520.135 868.0053) 
(list 3520.135 868.0156) 
(list 3520.135 868.0258) 
(list 3520.135 868.0361) 
(list 3520.135 868.0464) 
(list 3520.135 868.0567) 
(list 3520.135 868.0669) 
(list 3520.135 868.0772) 
(list 3520.135 868.0875) 
(list 3520.135 868.0978) 
(list 3520.135 868.1081) 
(list 3520.135 868.1183) 
(list 3520.135 868.1286) 
(list 3520.135 868.1389) 
(list 3520.135 868.1492) 
(list 3520.135 868.1594) 
(list 3520.135 868.1697) 
(list 3520.135 868.18) 
(list 3520 868.18)))
(apply 'command (append '("pline") coords '("c")))
(setq tap11 (ssadd (entlast) tap11))
(command "_mirror" (entlast) "" "3520,900" "3520,901" "No")
(setq tap11 (ssadd (entlast) tap11))
(setq coords (list 
(list 3520.4553 867.81) 
(list 3520.4452 867.81) 
(list 3520.4451 867.8203) 
(list 3520.4441 867.8306) 
(list 3520.4423 867.8408) 
(list 3520.4398 867.8511) 
(list 3520.4365 867.8614) 
(list 3520.4326 867.8717) 
(list 3520.4282 867.8819) 
(list 3520.4235 867.8922) 
(list 3520.4185 867.9025) 
(list 3520.4134 867.9128) 
(list 3520.4084 867.9231) 
(list 3520.4036 867.9333) 
(list 3520.3991 867.9436) 
(list 3520.3953 867.9539) 
(list 3520.392 867.9642) 
(list 3520.3895 867.9744) 
(list 3520.3879 867.9847) 
(list 3520.3872 867.995) 
(list 3520.3875 868.0053) 
(list 3520.3887 868.0156) 
(list 3520.3909 868.0258) 
(list 3520.394 868.0361) 
(list 3520.3978 868.0464) 
(list 3520.4024 868.0567) 
(list 3520.4076 868.0669) 
(list 3520.4132 868.0772) 
(list 3520.419 868.0875) 
(list 3520.4249 868.0978) 
(list 3520.4308 868.1081) 
(list 3520.4363 868.1183) 
(list 3520.4415 868.1286) 
(list 3520.446 868.1389) 
(list 3520.4497 868.1492) 
(list 3520.4526 868.1594) 
(list 3520.4544 868.1697) 
(list 3520.4553 868.18) 
(list 3520.4553 868.18)))
(apply 'command (append '("pline") coords '("c")))
(setq tap11 (ssadd (entlast) tap11))
(command "_mirror" (entlast) "" "3520,900" "3520,901" "No")
(setq tap11 (ssadd (entlast) tap11))
(setq coords (list 
(list 3521.132 867.81) 
(list 3520.4553 867.81) 
(list 3520.4553 867.8203) 
(list 3520.4553 867.8306) 
(list 3520.4553 867.8408) 
(list 3520.4553 867.8511) 
(list 3520.4553 867.8614) 
(list 3520.4553 867.8717) 
(list 3520.4553 867.8819) 
(list 3520.4553 867.8922) 
(list 3520.4553 867.9025) 
(list 3520.4553 867.9128) 
(list 3520.4553 867.9231) 
(list 3520.4553 867.9333) 
(list 3520.4553 867.9436) 
(list 3520.4553 867.9539) 
(list 3520.4553 867.9642) 
(list 3520.4553 867.9744) 
(list 3520.4553 867.9847) 
(list 3520.4553 867.995) 
(list 3520.4553 868.0053) 
(list 3520.4553 868.0156) 
(list 3520.4553 868.0258) 
(list 3520.4553 868.0361) 
(list 3520.4553 868.0464) 
(list 3520.4553 868.0567) 
(list 3520.4553 868.0669) 
(list 3520.4553 868.0772) 
(list 3520.4553 868.0875) 
(list 3520.4553 868.0978) 
(list 3520.4553 868.1081) 
(list 3520.4553 868.1183) 
(list 3520.4553 868.1286) 
(list 3520.4553 868.1389) 
(list 3520.4553 868.1492) 
(list 3520.4553 868.1594) 
(list 3520.4553 868.1697) 
(list 3520.4553 868.18) 
(list 3521.132 868.18)))
(apply 'command (append '("pline") coords '("c")))
(setq tap11 (ssadd (entlast) tap11))
(command "_mirror" (entlast) "" "3520,900" "3520,901" "No")
(setq tap11 (ssadd (entlast) tap11))
(setq coords (list 
(list 3520 868.18) 
(list 3520.135 868.18) 
(list 3520.135 868.1903) 
(list 3520.135 868.2006) 
(list 3520.135 868.2108) 
(list 3520.135 868.2211) 
(list 3520.135 868.2314) 
(list 3520.135 868.2417) 
(list 3520.135 868.2519) 
(list 3520.135 868.2622) 
(list 3520.135 868.2725) 
(list 3520.135 868.2828) 
(list 3520.135 868.2931) 
(list 3520.135 868.3033) 
(list 3520.135 868.3136) 
(list 3520.135 868.3239) 
(list 3520.135 868.3342) 
(list 3520.135 868.3444) 
(list 3520.135 868.3547) 
(list 3520.135 868.365) 
(list 3520.135 868.3753) 
(list 3520.135 868.3856) 
(list 3520.135 868.3958) 
(list 3520.135 868.4061) 
(list 3520.135 868.4164) 
(list 3520.135 868.4267) 
(list 3520.135 868.4369) 
(list 3520.135 868.4472) 
(list 3520.135 868.4575) 
(list 3520.135 868.4678) 
(list 3520.135 868.4781) 
(list 3520.135 868.4883) 
(list 3520.135 868.4986) 
(list 3520.135 868.5089) 
(list 3520.135 868.5192) 
(list 3520.135 868.5294) 
(list 3520.135 868.5397) 
(list 3520.135 868.55) 
(list 3520 868.55)))
(apply 'command (append '("pline") coords '("c")))
(setq tap11 (ssadd (entlast) tap11))
(command "_mirror" (entlast) "" "3520,900" "3520,901" "No")
(setq tap11 (ssadd (entlast) tap11))
(setq coords (list 
(list 3520.4653 868.18) 
(list 3520.4553 868.18) 
(list 3520.455 868.1903) 
(list 3520.4536 868.2006) 
(list 3520.4512 868.2108) 
(list 3520.4477 868.2211) 
(list 3520.4434 868.2314) 
(list 3520.4382 868.2417) 
(list 3520.4324 868.2519) 
(list 3520.4261 868.2622) 
(list 3520.4195 868.2725) 
(list 3520.4129 868.2828) 
(list 3520.4063 868.2931) 
(list 3520.4001 868.3033) 
(list 3520.3944 868.3136) 
(list 3520.3894 868.3239) 
(list 3520.3853 868.3342) 
(list 3520.3822 868.3444) 
(list 3520.3801 868.3547) 
(list 3520.3793 868.365) 
(list 3520.3797 868.3753) 
(list 3520.3813 868.3856) 
(list 3520.3842 868.3958) 
(list 3520.3881 868.4061) 
(list 3520.3931 868.4164) 
(list 3520.399 868.4267) 
(list 3520.4056 868.4369) 
(list 3520.4127 868.4472) 
(list 3520.4201 868.4575) 
(list 3520.4276 868.4678) 
(list 3520.4349 868.4781) 
(list 3520.4419 868.4883) 
(list 3520.4483 868.4986) 
(list 3520.4539 868.5089) 
(list 3520.4586 868.5192) 
(list 3520.4621 868.5294) 
(list 3520.4644 868.5397) 
(list 3520.4653 868.55) 
(list 3520.4653 868.55)))
(apply 'command (append '("pline") coords '("c")))
(setq tap11 (ssadd (entlast) tap11))
(command "_mirror" (entlast) "" "3520,900" "3520,901" "No")
(setq tap11 (ssadd (entlast) tap11))
(setq coords (list 
(list 3521.132 868.18) 
(list 3520.4653 868.18) 
(list 3520.4653 868.1903) 
(list 3520.4653 868.2006) 
(list 3520.4653 868.2108) 
(list 3520.4653 868.2211) 
(list 3520.4653 868.2314) 
(list 3520.4653 868.2417) 
(list 3520.4653 868.2519) 
(list 3520.4653 868.2622) 
(list 3520.4653 868.2725) 
(list 3520.4653 868.2828) 
(list 3520.4653 868.2931) 
(list 3520.4653 868.3033) 
(list 3520.4653 868.3136) 
(list 3520.4653 868.3239) 
(list 3520.4653 868.3342) 
(list 3520.4653 868.3444) 
(list 3520.4653 868.3547) 
(list 3520.4653 868.365) 
(list 3520.4653 868.3753) 
(list 3520.4653 868.3856) 
(list 3520.4653 868.3958) 
(list 3520.4653 868.4061) 
(list 3520.4653 868.4164) 
(list 3520.4653 868.4267) 
(list 3520.4653 868.4369) 
(list 3520.4653 868.4472) 
(list 3520.4653 868.4575) 
(list 3520.4653 868.4678) 
(list 3520.4653 868.4781) 
(list 3520.4653 868.4883) 
(list 3520.4653 868.4986) 
(list 3520.4653 868.5089) 
(list 3520.4653 868.5192) 
(list 3520.4653 868.5294) 
(list 3520.4653 868.5397) 
(list 3520.4653 868.55) 
(list 3521.132 868.55)))
(apply 'command (append '("pline") coords '("c")))
(setq tap11 (ssadd (entlast) tap11))
(command "_mirror" (entlast) "" "3520,900" "3520,901" "No")
(setq tap11 (ssadd (entlast) tap11))
(setq coords (list 
(list 3520 868.55) 
(list 3520.135 868.55) 
(list 3520.135 868.5603) 
(list 3520.135 868.5706) 
(list 3520.135 868.5808) 
(list 3520.135 868.5911) 
(list 3520.135 868.6014) 
(list 3520.135 868.6117) 
(list 3520.135 868.6219) 
(list 3520.135 868.6322) 
(list 3520.135 868.6425) 
(list 3520.135 868.6528) 
(list 3520.135 868.6631) 
(list 3520.135 868.6733) 
(list 3520.135 868.6836) 
(list 3520.135 868.6939) 
(list 3520.135 868.7042) 
(list 3520.135 868.7144) 
(list 3520.135 868.7247) 
(list 3520.135 868.735) 
(list 3520.135 868.7453) 
(list 3520.135 868.7556) 
(list 3520.135 868.7658) 
(list 3520.135 868.7761) 
(list 3520.135 868.7864) 
(list 3520.135 868.7967) 
(list 3520.135 868.8069) 
(list 3520.135 868.8172) 
(list 3520.135 868.8275) 
(list 3520.135 868.8378) 
(list 3520.135 868.8481) 
(list 3520.135 868.8583) 
(list 3520.135 868.8686) 
(list 3520.135 868.8789) 
(list 3520.135 868.8892) 
(list 3520.135 868.8994) 
(list 3520.135 868.9097) 
(list 3520.135 868.92) 
(list 3520 868.92)))
(apply 'command (append '("pline") coords '("c")))
(setq tap11 (ssadd (entlast) tap11))
(command "_mirror" (entlast) "" "3520,900" "3520,901" "No")
(setq tap11 (ssadd (entlast) tap11))
(setq coords (list 
(list 3520.4754 868.55) 
(list 3520.4653 868.55) 
(list 3520.4649 868.5603) 
(list 3520.4631 868.5706) 
(list 3520.46 868.5808) 
(list 3520.4557 868.5911) 
(list 3520.4502 868.6014) 
(list 3520.4438 868.6117) 
(list 3520.4365 868.6219) 
(list 3520.4287 868.6322) 
(list 3520.4206 868.6425) 
(list 3520.4124 868.6528) 
(list 3520.4043 868.6631) 
(list 3520.3967 868.6733) 
(list 3520.3897 868.6836) 
(list 3520.3836 868.6939) 
(list 3520.3786 868.7042) 
(list 3520.3748 868.7144) 
(list 3520.3723 868.7247) 
(list 3520.3714 868.735) 
(list 3520.3719 868.7453) 
(list 3520.3739 868.7556) 
(list 3520.3774 868.7658) 
(list 3520.3823 868.7761) 
(list 3520.3884 868.7864) 
(list 3520.3955 868.7967) 
(list 3520.4035 868.8069) 
(list 3520.4122 868.8172) 
(list 3520.4211 868.8275) 
(list 3520.4302 868.8378) 
(list 3520.4391 868.8481) 
(list 3520.4475 868.8583) 
(list 3520.4552 868.8686) 
(list 3520.4619 868.8789) 
(list 3520.4674 868.8892) 
(list 3520.4716 868.8994) 
(list 3520.4743 868.9097) 
(list 3520.4754 868.92) 
(list 3520.4754 868.92)))
(apply 'command (append '("pline") coords '("c")))
(setq tap11 (ssadd (entlast) tap11))
(command "_mirror" (entlast) "" "3520,900" "3520,901" "No")
(setq tap11 (ssadd (entlast) tap11))
(setq coords (list 
(list 3521.132 868.55) 
(list 3520.4754 868.55) 
(list 3520.4754 868.5603) 
(list 3520.4754 868.5706) 
(list 3520.4754 868.5808) 
(list 3520.4754 868.5911) 
(list 3520.4754 868.6014) 
(list 3520.4754 868.6117) 
(list 3520.4754 868.6219) 
(list 3520.4754 868.6322) 
(list 3520.4754 868.6425) 
(list 3520.4754 868.6528) 
(list 3520.4754 868.6631) 
(list 3520.4754 868.6733) 
(list 3520.4754 868.6836) 
(list 3520.4754 868.6939) 
(list 3520.4754 868.7042) 
(list 3520.4754 868.7144) 
(list 3520.4754 868.7247) 
(list 3520.4754 868.735) 
(list 3520.4754 868.7453) 
(list 3520.4754 868.7556) 
(list 3520.4754 868.7658) 
(list 3520.4754 868.7761) 
(list 3520.4754 868.7864) 
(list 3520.4754 868.7967) 
(list 3520.4754 868.8069) 
(list 3520.4754 868.8172) 
(list 3520.4754 868.8275) 
(list 3520.4754 868.8378) 
(list 3520.4754 868.8481) 
(list 3520.4754 868.8583) 
(list 3520.4754 868.8686) 
(list 3520.4754 868.8789) 
(list 3520.4754 868.8892) 
(list 3520.4754 868.8994) 
(list 3520.4754 868.9097) 
(list 3520.4754 868.92) 
(list 3521.132 868.92)))
(apply 'command (append '("pline") coords '("c")))
(setq tap11 (ssadd (entlast) tap11))
(command "_mirror" (entlast) "" "3520,900" "3520,901" "No")
(setq tap11 (ssadd (entlast) tap11))
(setq coords (list 
(list 3520 868.92) 
(list 3520.135 868.92) 
(list 3520.135 868.9303) 
(list 3520.135 868.9406) 
(list 3520.135 868.9508) 
(list 3520.135 868.9611) 
(list 3520.135 868.9714) 
(list 3520.135 868.9817) 
(list 3520.135 868.9919) 
(list 3520.135 869.0022) 
(list 3520.135 869.0125) 
(list 3520.135 869.0228) 
(list 3520.135 869.0331) 
(list 3520.135 869.0433) 
(list 3520.135 869.0536) 
(list 3520.135 869.0639) 
(list 3520.135 869.0742) 
(list 3520.135 869.0844) 
(list 3520.135 869.0947) 
(list 3520.135 869.105) 
(list 3520.135 869.1153) 
(list 3520.135 869.1256) 
(list 3520.135 869.1358) 
(list 3520.135 869.1461) 
(list 3520.135 869.1564) 
(list 3520.135 869.1667) 
(list 3520.135 869.1769) 
(list 3520.135 869.1872) 
(list 3520.135 869.1975) 
(list 3520.135 869.2078) 
(list 3520.135 869.2181) 
(list 3520.135 869.2283) 
(list 3520.135 869.2386) 
(list 3520.135 869.2489) 
(list 3520.135 869.2592) 
(list 3520.135 869.2694) 
(list 3520.135 869.2797) 
(list 3520.135 869.29) 
(list 3520 869.29)))
(apply 'command (append '("pline") coords '("c")))
(setq tap11 (ssadd (entlast) tap11))
(command "_mirror" (entlast) "" "3520,900" "3520,901" "No")
(setq tap11 (ssadd (entlast) tap11))
(setq coords (list 
(list 3520.4855 868.92) 
(list 3520.4754 868.92) 
(list 3520.4749 868.9303) 
(list 3520.4727 868.9406) 
(list 3520.4689 868.9508) 
(list 3520.4637 868.9611) 
(list 3520.4571 868.9714) 
(list 3520.4493 868.9817) 
(list 3520.4407 868.9919) 
(list 3520.4314 869.0022) 
(list 3520.4217 869.0125) 
(list 3520.4119 869.0228) 
(list 3520.4023 869.0331) 
(list 3520.3933 869.0433) 
(list 3520.385 869.0536) 
(list 3520.3778 869.0639) 
(list 3520.3718 869.0742) 
(list 3520.3674 869.0844) 
(list 3520.3645 869.0947) 
(list 3520.3634 869.105) 
(list 3520.3641 869.1153) 
(list 3520.3666 869.1256) 
(list 3520.3707 869.1358) 
(list 3520.3765 869.1461) 
(list 3520.3837 869.1564) 
(list 3520.3921 869.1667) 
(list 3520.4015 869.1769) 
(list 3520.4117 869.1872) 
(list 3520.4222 869.1975) 
(list 3520.4328 869.2078) 
(list 3520.4432 869.2181) 
(list 3520.453 869.2283) 
(list 3520.462 869.2386) 
(list 3520.4698 869.2489) 
(list 3520.4763 869.2592) 
(list 3520.4811 869.2694) 
(list 3520.4842 869.2797) 
(list 3520.4855 869.29) 
(list 3520.4855 869.29)))
(apply 'command (append '("pline") coords '("c")))
(setq tap11 (ssadd (entlast) tap11))
(command "_mirror" (entlast) "" "3520,900" "3520,901" "No")
(setq tap11 (ssadd (entlast) tap11))
(setq coords (list 
(list 3521.132 868.92) 
(list 3520.4855 868.92) 
(list 3520.4855 868.9303) 
(list 3520.4855 868.9406) 
(list 3520.4855 868.9508) 
(list 3520.4855 868.9611) 
(list 3520.4855 868.9714) 
(list 3520.4855 868.9817) 
(list 3520.4855 868.9919) 
(list 3520.4855 869.0022) 
(list 3520.4855 869.0125) 
(list 3520.4855 869.0228) 
(list 3520.4855 869.0331) 
(list 3520.4855 869.0433) 
(list 3520.4855 869.0536) 
(list 3520.4855 869.0639) 
(list 3520.4855 869.0742) 
(list 3520.4855 869.0844) 
(list 3520.4855 869.0947) 
(list 3520.4855 869.105) 
(list 3520.4855 869.1153) 
(list 3520.4855 869.1256) 
(list 3520.4855 869.1358) 
(list 3520.4855 869.1461) 
(list 3520.4855 869.1564) 
(list 3520.4855 869.1667) 
(list 3520.4855 869.1769) 
(list 3520.4855 869.1872) 
(list 3520.4855 869.1975) 
(list 3520.4855 869.2078) 
(list 3520.4855 869.2181) 
(list 3520.4855 869.2283) 
(list 3520.4855 869.2386) 
(list 3520.4855 869.2489) 
(list 3520.4855 869.2592) 
(list 3520.4855 869.2694) 
(list 3520.4855 869.2797) 
(list 3520.4855 869.29) 
(list 3521.132 869.29)))
(apply 'command (append '("pline") coords '("c")))
(setq tap11 (ssadd (entlast) tap11))
(command "_mirror" (entlast) "" "3520,900" "3520,901" "No")
(setq tap11 (ssadd (entlast) tap11))
(setq coords (list 
(list 3520 869.29) 
(list 3520.135 869.29) 
(list 3520.135 869.3003) 
(list 3520.135 869.3106) 
(list 3520.135 869.3208) 
(list 3520.135 869.3311) 
(list 3520.135 869.3414) 
(list 3520.135 869.3517) 
(list 3520.135 869.3619) 
(list 3520.135 869.3722) 
(list 3520.135 869.3825) 
(list 3520.135 869.3928) 
(list 3520.135 869.4031) 
(list 3520.135 869.4133) 
(list 3520.135 869.4236) 
(list 3520.135 869.4339) 
(list 3520.135 869.4442) 
(list 3520.135 869.4544) 
(list 3520.135 869.4647) 
(list 3520.135 869.475) 
(list 3520.135 869.4853) 
(list 3520.135 869.4956) 
(list 3520.135 869.5058) 
(list 3520.135 869.5161) 
(list 3520.135 869.5264) 
(list 3520.135 869.5367) 
(list 3520.135 869.5469) 
(list 3520.135 869.5572) 
(list 3520.135 869.5675) 
(list 3520.135 869.5778) 
(list 3520.135 869.5881) 
(list 3520.135 869.5983) 
(list 3520.135 869.6086) 
(list 3520.135 869.6189) 
(list 3520.135 869.6292) 
(list 3520.135 869.6394) 
(list 3520.135 869.6497) 
(list 3520.135 869.66) 
(list 3520 869.66)))
(apply 'command (append '("pline") coords '("c")))
(setq tap11 (ssadd (entlast) tap11))
(command "_mirror" (entlast) "" "3520,900" "3520,901" "No")
(setq tap11 (ssadd (entlast) tap11))
(setq coords (list 
(list 3520.4955 869.29) 
(list 3520.4855 869.29) 
(list 3520.4848 869.3003) 
(list 3520.4822 869.3106) 
(list 3520.4778 869.3208) 
(list 3520.4716 869.3311) 
(list 3520.4639 869.3414) 
(list 3520.4549 869.3517) 
(list 3520.4448 869.3619) 
(list 3520.434 869.3722) 
(list 3520.4227 869.3825) 
(list 3520.4114 869.3928) 
(list 3520.4003 869.4031) 
(list 3520.3898 869.4133) 
(list 3520.3803 869.4236) 
(list 3520.3719 869.4339) 
(list 3520.3651 869.4442) 
(list 3520.36 869.4544) 
(list 3520.3567 869.4647) 
(list 3520.3555 869.475) 
(list 3520.3563 869.4853) 
(list 3520.3592 869.4956) 
(list 3520.364 869.5058) 
(list 3520.3706 869.5161) 
(list 3520.379 869.5264) 
(list 3520.3887 869.5367) 
(list 3520.3995 869.5469) 
(list 3520.4112 869.5572) 
(list 3520.4233 869.5675) 
(list 3520.4355 869.5778) 
(list 3520.4474 869.5881) 
(list 3520.4586 869.5983) 
(list 3520.4689 869.6086) 
(list 3520.4778 869.6189) 
(list 3520.4851 869.6292) 
(list 3520.4907 869.6394) 
(list 3520.4942 869.6497) 
(list 3520.4955 869.66) 
(list 3520.4955 869.66)))
(apply 'command (append '("pline") coords '("c")))
(setq tap11 (ssadd (entlast) tap11))
(command "_mirror" (entlast) "" "3520,900" "3520,901" "No")
(setq tap11 (ssadd (entlast) tap11))
(setq coords (list 
(list 3521.132 869.29) 
(list 3520.4955 869.29) 
(list 3520.4955 869.3003) 
(list 3520.4955 869.3106) 
(list 3520.4955 869.3208) 
(list 3520.4955 869.3311) 
(list 3520.4955 869.3414) 
(list 3520.4955 869.3517) 
(list 3520.4955 869.3619) 
(list 3520.4955 869.3722) 
(list 3520.4955 869.3825) 
(list 3520.4955 869.3928) 
(list 3520.4955 869.4031) 
(list 3520.4955 869.4133) 
(list 3520.4955 869.4236) 
(list 3520.4955 869.4339) 
(list 3520.4955 869.4442) 
(list 3520.4955 869.4544) 
(list 3520.4955 869.4647) 
(list 3520.4955 869.475) 
(list 3520.4955 869.4853) 
(list 3520.4955 869.4956) 
(list 3520.4955 869.5058) 
(list 3520.4955 869.5161) 
(list 3520.4955 869.5264) 
(list 3520.4955 869.5367) 
(list 3520.4955 869.5469) 
(list 3520.4955 869.5572) 
(list 3520.4955 869.5675) 
(list 3520.4955 869.5778) 
(list 3520.4955 869.5881) 
(list 3520.4955 869.5983) 
(list 3520.4955 869.6086) 
(list 3520.4955 869.6189) 
(list 3520.4955 869.6292) 
(list 3520.4955 869.6394) 
(list 3520.4955 869.6497) 
(list 3520.4955 869.66) 
(list 3521.132 869.66)))
(apply 'command (append '("pline") coords '("c")))
(setq tap11 (ssadd (entlast) tap11))
(command "_mirror" (entlast) "" "3520,900" "3520,901" "No")
(setq tap11 (ssadd (entlast) tap11))
(setq coords (list 
(list 3520 869.66) 
(list 3520.135 869.66) 
(list 3520.135 869.6703) 
(list 3520.135 869.6806) 
(list 3520.135 869.6908) 
(list 3520.135 869.7011) 
(list 3520.135 869.7114) 
(list 3520.135 869.7217) 
(list 3520.135 869.7319) 
(list 3520.135 869.7422) 
(list 3520.135 869.7525) 
(list 3520.135 869.7628) 
(list 3520.135 869.7731) 
(list 3520.135 869.7833) 
(list 3520.135 869.7936) 
(list 3520.135 869.8039) 
(list 3520.135 869.8142) 
(list 3520.135 869.8244) 
(list 3520.135 869.8347) 
(list 3520.135 869.845) 
(list 3520.135 869.8553) 
(list 3520.135 869.8656) 
(list 3520.135 869.8758) 
(list 3520.135 869.8861) 
(list 3520.135 869.8964) 
(list 3520.135 869.9067) 
(list 3520.135 869.9169) 
(list 3520.135 869.9272) 
(list 3520.135 869.9375) 
(list 3520.135 869.9478) 
(list 3520.135 869.9581) 
(list 3520.135 869.9683) 
(list 3520.135 869.9786) 
(list 3520.135 869.9889) 
(list 3520.135 869.9992) 
(list 3520.135 870.0094) 
(list 3520.135 870.0197) 
(list 3520.135 870.03) 
(list 3520 870.03)))
(apply 'command (append '("pline") coords '("c")))
(setq tap11 (ssadd (entlast) tap11))
(command "_mirror" (entlast) "" "3520,900" "3520,901" "No")
(setq tap11 (ssadd (entlast) tap11))
(setq coords (list 
(list 3520.5056 869.66) 
(list 3520.4955 869.66) 
(list 3520.4947 869.6703) 
(list 3520.4917 869.6806) 
(list 3520.4866 869.6908) 
(list 3520.4796 869.7011) 
(list 3520.4708 869.7114) 
(list 3520.4605 869.7217) 
(list 3520.449 869.7319) 
(list 3520.4366 869.7422) 
(list 3520.4238 869.7525) 
(list 3520.4109 869.7628) 
(list 3520.3983 869.7731) 
(list 3520.3864 869.7833) 
(list 3520.3755 869.7936) 
(list 3520.3661 869.8039) 
(list 3520.3584 869.8142) 
(list 3520.3526 869.8244) 
(list 3520.3489 869.8347) 
(list 3520.3476 869.845) 
(list 3520.3485 869.8553) 
(list 3520.3518 869.8656) 
(list 3520.3573 869.8758) 
(list 3520.3648 869.8861) 
(list 3520.3742 869.8964) 
(list 3520.3852 869.9067) 
(list 3520.3975 869.9169) 
(list 3520.4107 869.9272) 
(list 3520.4243 869.9375) 
(list 3520.4381 869.9478) 
(list 3520.4515 869.9581) 
(list 3520.4642 869.9683) 
(list 3520.4757 869.9786) 
(list 3520.4858 869.9889) 
(list 3520.494 869.9992) 
(list 3520.5002 870.0094) 
(list 3520.5041 870.0197) 
(list 3520.5056 870.03) 
(list 3520.5056 870.03)))
(apply 'command (append '("pline") coords '("c")))
(setq tap11 (ssadd (entlast) tap11))
(command "_mirror" (entlast) "" "3520,900" "3520,901" "No")
(setq tap11 (ssadd (entlast) tap11))
(setq coords (list 
(list 3521.132 869.66) 
(list 3520.5056 869.66) 
(list 3520.5056 869.6703) 
(list 3520.5056 869.6806) 
(list 3520.5056 869.6908) 
(list 3520.5056 869.7011) 
(list 3520.5056 869.7114) 
(list 3520.5056 869.7217) 
(list 3520.5056 869.7319) 
(list 3520.5056 869.7422) 
(list 3520.5056 869.7525) 
(list 3520.5056 869.7628) 
(list 3520.5056 869.7731) 
(list 3520.5056 869.7833) 
(list 3520.5056 869.7936) 
(list 3520.5056 869.8039) 
(list 3520.5056 869.8142) 
(list 3520.5056 869.8244) 
(list 3520.5056 869.8347) 
(list 3520.5056 869.845) 
(list 3520.5056 869.8553) 
(list 3520.5056 869.8656) 
(list 3520.5056 869.8758) 
(list 3520.5056 869.8861) 
(list 3520.5056 869.8964) 
(list 3520.5056 869.9067) 
(list 3520.5056 869.9169) 
(list 3520.5056 869.9272) 
(list 3520.5056 869.9375) 
(list 3520.5056 869.9478) 
(list 3520.5056 869.9581) 
(list 3520.5056 869.9683) 
(list 3520.5056 869.9786) 
(list 3520.5056 869.9889) 
(list 3520.5056 869.9992) 
(list 3520.5056 870.0094) 
(list 3520.5056 870.0197) 
(list 3520.5056 870.03) 
(list 3521.132 870.03)))
(apply 'command (append '("pline") coords '("c")))
(setq tap11 (ssadd (entlast) tap11))
(command "_mirror" (entlast) "" "3520,900" "3520,901" "No")
(setq tap11 (ssadd (entlast) tap11))
(setq coords (list 
(list 3520 870.03) 
(list 3520.135 870.03) 
(list 3520.135 870.0403) 
(list 3520.135 870.0506) 
(list 3520.135 870.0608) 
(list 3520.135 870.0711) 
(list 3520.135 870.0814) 
(list 3520.135 870.0917) 
(list 3520.135 870.1019) 
(list 3520.135 870.1122) 
(list 3520.135 870.1225) 
(list 3520.135 870.1328) 
(list 3520.135 870.1431) 
(list 3520.135 870.1533) 
(list 3520.135 870.1636) 
(list 3520.135 870.1739) 
(list 3520.135 870.1842) 
(list 3520.135 870.1944) 
(list 3520.135 870.2047) 
(list 3520.135 870.215) 
(list 3520.135 870.2253) 
(list 3520.135 870.2356) 
(list 3520.135 870.2458) 
(list 3520.135 870.2561) 
(list 3520.135 870.2664) 
(list 3520.135 870.2767) 
(list 3520.135 870.2869) 
(list 3520.135 870.2972) 
(list 3520.135 870.3075) 
(list 3520.135 870.3178) 
(list 3520.135 870.3281) 
(list 3520.135 870.3383) 
(list 3520.135 870.3486) 
(list 3520.135 870.3589) 
(list 3520.135 870.3692) 
(list 3520.135 870.3794) 
(list 3520.135 870.3897) 
(list 3520.135 870.4) 
(list 3520 870.4)))
(apply 'command (append '("pline") coords '("c")))
(setq tap11 (ssadd (entlast) tap11))
(command "_mirror" (entlast) "" "3520,900" "3520,901" "No")
(setq tap11 (ssadd (entlast) tap11))
(setq coords (list 
(list 3520.5157 870.03) 
(list 3520.5056 870.03) 
(list 3520.5046 870.0403) 
(list 3520.5012 870.0506) 
(list 3520.4955 870.0608) 
(list 3520.4875 870.0711) 
(list 3520.4776 870.0814) 
(list 3520.466 870.0917) 
(list 3520.4531 870.1019) 
(list 3520.4392 870.1122) 
(list 3520.4249 870.1225) 
(list 3520.4104 870.1328) 
(list 3520.3963 870.1431) 
(list 3520.383 870.1533) 
(list 3520.3708 870.1636) 
(list 3520.3603 870.1739) 
(list 3520.3516 870.1842) 
(list 3520.3452 870.1944) 
(list 3520.3411 870.2047) 
(list 3520.3396 870.215) 
(list 3520.3407 870.2253) 
(list 3520.3444 870.2356) 
(list 3520.3505 870.2458) 
(list 3520.359 870.2561) 
(list 3520.3695 870.2664) 
(list 3520.3818 870.2767) 
(list 3520.3955 870.2869) 
(list 3520.4102 870.2972) 
(list 3520.4254 870.3075) 
(list 3520.4407 870.3178) 
(list 3520.4556 870.3281) 
(list 3520.4697 870.3383) 
(list 3520.4826 870.3486) 
(list 3520.4937 870.3589) 
(list 3520.5029 870.3692) 
(list 3520.5097 870.3794) 
(list 3520.514 870.3897) 
(list 3520.5157 870.4) 
(list 3520.5157 870.4)))
(apply 'command (append '("pline") coords '("c")))
(setq tap11 (ssadd (entlast) tap11))
(command "_mirror" (entlast) "" "3520,900" "3520,901" "No")
(setq tap11 (ssadd (entlast) tap11))
(setq coords (list 
(list 3521.132 870.03) 
(list 3520.5157 870.03) 
(list 3520.5157 870.0403) 
(list 3520.5157 870.0506) 
(list 3520.5157 870.0608) 
(list 3520.5157 870.0711) 
(list 3520.5157 870.0814) 
(list 3520.5157 870.0917) 
(list 3520.5157 870.1019) 
(list 3520.5157 870.1122) 
(list 3520.5157 870.1225) 
(list 3520.5157 870.1328) 
(list 3520.5157 870.1431) 
(list 3520.5157 870.1533) 
(list 3520.5157 870.1636) 
(list 3520.5157 870.1739) 
(list 3520.5157 870.1842) 
(list 3520.5157 870.1944) 
(list 3520.5157 870.2047) 
(list 3520.5157 870.215) 
(list 3520.5157 870.2253) 
(list 3520.5157 870.2356) 
(list 3520.5157 870.2458) 
(list 3520.5157 870.2561) 
(list 3520.5157 870.2664) 
(list 3520.5157 870.2767) 
(list 3520.5157 870.2869) 
(list 3520.5157 870.2972) 
(list 3520.5157 870.3075) 
(list 3520.5157 870.3178) 
(list 3520.5157 870.3281) 
(list 3520.5157 870.3383) 
(list 3520.5157 870.3486) 
(list 3520.5157 870.3589) 
(list 3520.5157 870.3692) 
(list 3520.5157 870.3794) 
(list 3520.5157 870.3897) 
(list 3520.5157 870.4) 
(list 3521.132 870.4)))
(apply 'command (append '("pline") coords '("c")))
(setq tap11 (ssadd (entlast) tap11))
(command "_mirror" (entlast) "" "3520,900" "3520,901" "No")
(setq tap11 (ssadd (entlast) tap11))
(setq coords (list 
(list 3520 870.4) 
(list 3520.135 870.4) 
(list 3520.135 870.4103) 
(list 3520.135 870.4206) 
(list 3520.135 870.4308) 
(list 3520.135 870.4411) 
(list 3520.135 870.4514) 
(list 3520.135 870.4617) 
(list 3520.135 870.4719) 
(list 3520.135 870.4822) 
(list 3520.135 870.4925) 
(list 3520.135 870.5028) 
(list 3520.135 870.5131) 
(list 3520.135 870.5233) 
(list 3520.135 870.5336) 
(list 3520.135 870.5439) 
(list 3520.135 870.5542) 
(list 3520.135 870.5644) 
(list 3520.135 870.5747) 
(list 3520.135 870.585) 
(list 3520.135 870.5953) 
(list 3520.135 870.6056) 
(list 3520.135 870.6158) 
(list 3520.135 870.6261) 
(list 3520.135 870.6364) 
(list 3520.135 870.6467) 
(list 3520.135 870.6569) 
(list 3520.135 870.6672) 
(list 3520.135 870.6775) 
(list 3520.135 870.6878) 
(list 3520.135 870.6981) 
(list 3520.135 870.7083) 
(list 3520.135 870.7186) 
(list 3520.135 870.7289) 
(list 3520.135 870.7392) 
(list 3520.135 870.7494) 
(list 3520.135 870.7597) 
(list 3520.135 870.77) 
(list 3520 870.77)))
(apply 'command (append '("pline") coords '("c")))
(setq tap11 (ssadd (entlast) tap11))
(command "_mirror" (entlast) "" "3520,900" "3520,901" "No")
(setq tap11 (ssadd (entlast) tap11))
(setq coords (list 
(list 3520.5257 870.4) 
(list 3520.5157 870.4) 
(list 3520.5146 870.4103) 
(list 3520.5108 870.4206) 
(list 3520.5043 870.4308) 
(list 3520.4955 870.4411) 
(list 3520.4845 870.4514) 
(list 3520.4716 870.4617) 
(list 3520.4573 870.4719) 
(list 3520.4419 870.4822) 
(list 3520.4259 870.4925) 
(list 3520.4099 870.5028) 
(list 3520.3943 870.5131) 
(list 3520.3795 870.5233) 
(list 3520.3661 870.5336) 
(list 3520.3545 870.5439) 
(list 3520.3449 870.5542) 
(list 3520.3378 870.5644) 
(list 3520.3334 870.5747) 
(list 3520.3317 870.585) 
(list 3520.3329 870.5953) 
(list 3520.337 870.6056) 
(list 3520.3438 870.6158) 
(list 3520.3532 870.6261) 
(list 3520.3648 870.6364) 
(list 3520.3784 870.6467) 
(list 3520.3935 870.6569) 
(list 3520.4097 870.6672) 
(list 3520.4265 870.6775) 
(list 3520.4433 870.6878) 
(list 3520.4598 870.6981) 
(list 3520.4753 870.7083) 
(list 3520.4894 870.7186) 
(list 3520.5017 870.7289) 
(list 3520.5117 870.7392) 
(list 3520.5192 870.7494) 
(list 3520.524 870.7597) 
(list 3520.5257 870.77) 
(list 3520.5257 870.77)))
(apply 'command (append '("pline") coords '("c")))
(setq tap11 (ssadd (entlast) tap11))
(command "_mirror" (entlast) "" "3520,900" "3520,901" "No")
(setq tap11 (ssadd (entlast) tap11))
(setq coords (list 
(list 3521.132 870.4) 
(list 3520.5257 870.4) 
(list 3520.5257 870.4103) 
(list 3520.5257 870.4206) 
(list 3520.5257 870.4308) 
(list 3520.5257 870.4411) 
(list 3520.5257 870.4514) 
(list 3520.5257 870.4617) 
(list 3520.5257 870.4719) 
(list 3520.5257 870.4822) 
(list 3520.5257 870.4925) 
(list 3520.5257 870.5028) 
(list 3520.5257 870.5131) 
(list 3520.5257 870.5233) 
(list 3520.5257 870.5336) 
(list 3520.5257 870.5439) 
(list 3520.5257 870.5542) 
(list 3520.5257 870.5644) 
(list 3520.5257 870.5747) 
(list 3520.5257 870.585) 
(list 3520.5257 870.5953) 
(list 3520.5257 870.6056) 
(list 3520.5257 870.6158) 
(list 3520.5257 870.6261) 
(list 3520.5257 870.6364) 
(list 3520.5257 870.6467) 
(list 3520.5257 870.6569) 
(list 3520.5257 870.6672) 
(list 3520.5257 870.6775) 
(list 3520.5257 870.6878) 
(list 3520.5257 870.6981) 
(list 3520.5257 870.7083) 
(list 3520.5257 870.7186) 
(list 3520.5257 870.7289) 
(list 3520.5257 870.7392) 
(list 3520.5257 870.7494) 
(list 3520.5257 870.7597) 
(list 3520.5257 870.77) 
(list 3521.132 870.77)))
(apply 'command (append '("pline") coords '("c")))
(setq tap11 (ssadd (entlast) tap11))
(command "_mirror" (entlast) "" "3520,900" "3520,901" "No")
(setq tap11 (ssadd (entlast) tap11))
(setq coords (list 
(list 3520 870.77) 
(list 3520.135 870.77) 
(list 3520.135 870.7803) 
(list 3520.135 870.7906) 
(list 3520.135 870.8008) 
(list 3520.135 870.8111) 
(list 3520.135 870.8214) 
(list 3520.135 870.8317) 
(list 3520.135 870.8419) 
(list 3520.135 870.8522) 
(list 3520.135 870.8625) 
(list 3520.135 870.8728) 
(list 3520.135 870.8831) 
(list 3520.135 870.8933) 
(list 3520.135 870.9036) 
(list 3520.135 870.9139) 
(list 3520.135 870.9242) 
(list 3520.135 870.9344) 
(list 3520.135 870.9447) 
(list 3520.135 870.955) 
(list 3520.135 870.9653) 
(list 3520.135 870.9756) 
(list 3520.135 870.9858) 
(list 3520.135 870.9961) 
(list 3520.135 871.0064) 
(list 3520.135 871.0167) 
(list 3520.135 871.0269) 
(list 3520.135 871.0372) 
(list 3520.135 871.0475) 
(list 3520.135 871.0578) 
(list 3520.135 871.0681) 
(list 3520.135 871.0783) 
(list 3520.135 871.0886) 
(list 3520.135 871.0989) 
(list 3520.135 871.1092) 
(list 3520.135 871.1194) 
(list 3520.135 871.1297) 
(list 3520.135 871.14) 
(list 3520 871.14)))
(apply 'command (append '("pline") coords '("c")))
(setq tap11 (ssadd (entlast) tap11))
(command "_mirror" (entlast) "" "3520,900" "3520,901" "No")
(setq tap11 (ssadd (entlast) tap11))
(setq coords (list 
(list 3520.5358 870.77) 
(list 3520.5257 870.77) 
(list 3520.5245 870.7803) 
(list 3520.5203 870.7906) 
(list 3520.5132 870.8008) 
(list 3520.5035 870.8111) 
(list 3520.4913 870.8214) 
(list 3520.4772 870.8317) 
(list 3520.4614 870.8419) 
(list 3520.4445 870.8522) 
(list 3520.427 870.8625) 
(list 3520.4094 870.8728) 
(list 3520.3923 870.8831) 
(list 3520.3761 870.8933) 
(list 3520.3614 870.9036) 
(list 3520.3486 870.9139) 
(list 3520.3382 870.9242) 
(list 3520.3304 870.9344) 
(list 3520.3256 870.9447) 
(list 3520.3238 870.955) 
(list 3520.3251 870.9653) 
(list 3520.3296 870.9756) 
(list 3520.3371 870.9858) 
(list 3520.3473 870.9961) 
(list 3520.3601 871.0064) 
(list 3520.3749 871.0167) 
(list 3520.3915 871.0269) 
(list 3520.4092 871.0372) 
(list 3520.4275 871.0475) 
(list 3520.446 871.0578) 
(list 3520.4639 871.0681) 
(list 3520.4809 871.0783) 
(list 3520.4963 871.0886) 
(list 3520.5096 871.0989) 
(list 3520.5206 871.1092) 
(list 3520.5288 871.1194) 
(list 3520.5339 871.1297) 
(list 3520.5358 871.14) 
(list 3520.5358 871.14)))
(apply 'command (append '("pline") coords '("c")))
(setq tap11 (ssadd (entlast) tap11))
(command "_mirror" (entlast) "" "3520,900" "3520,901" "No")
(setq tap11 (ssadd (entlast) tap11))
(setq coords (list 
(list 3521.132 870.77) 
(list 3520.5358 870.77) 
(list 3520.5358 870.7803) 
(list 3520.5358 870.7906) 
(list 3520.5358 870.8008) 
(list 3520.5358 870.8111) 
(list 3520.5358 870.8214) 
(list 3520.5358 870.8317) 
(list 3520.5358 870.8419) 
(list 3520.5358 870.8522) 
(list 3520.5358 870.8625) 
(list 3520.5358 870.8728) 
(list 3520.5358 870.8831) 
(list 3520.5358 870.8933) 
(list 3520.5358 870.9036) 
(list 3520.5358 870.9139) 
(list 3520.5358 870.9242) 
(list 3520.5358 870.9344) 
(list 3520.5358 870.9447) 
(list 3520.5358 870.955) 
(list 3520.5358 870.9653) 
(list 3520.5358 870.9756) 
(list 3520.5358 870.9858) 
(list 3520.5358 870.9961) 
(list 3520.5358 871.0064) 
(list 3520.5358 871.0167) 
(list 3520.5358 871.0269) 
(list 3520.5358 871.0372) 
(list 3520.5358 871.0475) 
(list 3520.5358 871.0578) 
(list 3520.5358 871.0681) 
(list 3520.5358 871.0783) 
(list 3520.5358 871.0886) 
(list 3520.5358 871.0989) 
(list 3520.5358 871.1092) 
(list 3520.5358 871.1194) 
(list 3520.5358 871.1297) 
(list 3520.5358 871.14) 
(list 3521.132 871.14)))
(apply 'command (append '("pline") coords '("c")))
(setq tap11 (ssadd (entlast) tap11))
(command "_mirror" (entlast) "" "3520,900" "3520,901" "No")
(setq tap11 (ssadd (entlast) tap11))
(setq coords (list 
(list 3520 871.14) 
(list 3520.135 871.14) 
(list 3520.135 871.1503) 
(list 3520.135 871.1606) 
(list 3520.135 871.1708) 
(list 3520.135 871.1811) 
(list 3520.135 871.1914) 
(list 3520.135 871.2017) 
(list 3520.135 871.2119) 
(list 3520.135 871.2222) 
(list 3520.135 871.2325) 
(list 3520.135 871.2428) 
(list 3520.135 871.2531) 
(list 3520.135 871.2633) 
(list 3520.135 871.2736) 
(list 3520.135 871.2839) 
(list 3520.135 871.2942) 
(list 3520.135 871.3044) 
(list 3520.135 871.3147) 
(list 3520.135 871.325) 
(list 3520.135 871.3353) 
(list 3520.135 871.3456) 
(list 3520.135 871.3558) 
(list 3520.135 871.3661) 
(list 3520.135 871.3764) 
(list 3520.135 871.3867) 
(list 3520.135 871.3969) 
(list 3520.135 871.4072) 
(list 3520.135 871.4175) 
(list 3520.135 871.4278) 
(list 3520.135 871.4381) 
(list 3520.135 871.4483) 
(list 3520.135 871.4586) 
(list 3520.135 871.4689) 
(list 3520.135 871.4792) 
(list 3520.135 871.4894) 
(list 3520.135 871.4997) 
(list 3520.135 871.51) 
(list 3520 871.51)))
(apply 'command (append '("pline") coords '("c")))
(setq tap11 (ssadd (entlast) tap11))
(command "_mirror" (entlast) "" "3520,900" "3520,901" "No")
(setq tap11 (ssadd (entlast) tap11))
(setq coords (list 
(list 3520.5459 871.14) 
(list 3520.5358 871.14) 
(list 3520.5344 871.1503) 
(list 3520.5298 871.1606) 
(list 3520.5221 871.1708) 
(list 3520.5114 871.1811) 
(list 3520.4982 871.1914) 
(list 3520.4827 871.2017) 
(list 3520.4655 871.2119) 
(list 3520.4471 871.2222) 
(list 3520.4281 871.2325) 
(list 3520.4089 871.2428) 
(list 3520.3902 871.2531) 
(list 3520.3727 871.2633) 
(list 3520.3567 871.2736) 
(list 3520.3428 871.2839) 
(list 3520.3315 871.2942) 
(list 3520.323 871.3044) 
(list 3520.3178 871.3147) 
(list 3520.3158 871.325) 
(list 3520.3173 871.3353) 
(list 3520.3222 871.3456) 
(list 3520.3303 871.3558) 
(list 3520.3415 871.3661) 
(list 3520.3554 871.3764) 
(list 3520.3715 871.3867) 
(list 3520.3895 871.3969) 
(list 3520.4087 871.4072) 
(list 3520.4286 871.4175) 
(list 3520.4486 871.4278) 
(list 3520.4681 871.4381) 
(list 3520.4864 871.4483) 
(list 3520.5031 871.4586) 
(list 3520.5176 871.4689) 
(list 3520.5295 871.4792) 
(list 3520.5383 871.4894) 
(list 3520.5438 871.4997) 
(list 3520.5459 871.51) 
(list 3520.5459 871.51)))
(apply 'command (append '("pline") coords '("c")))
(setq tap11 (ssadd (entlast) tap11))
(command "_mirror" (entlast) "" "3520,900" "3520,901" "No")
(setq tap11 (ssadd (entlast) tap11))
(setq coords (list 
(list 3521.132 871.14) 
(list 3520.5459 871.14) 
(list 3520.5459 871.1503) 
(list 3520.5459 871.1606) 
(list 3520.5459 871.1708) 
(list 3520.5459 871.1811) 
(list 3520.5459 871.1914) 
(list 3520.5459 871.2017) 
(list 3520.5459 871.2119) 
(list 3520.5459 871.2222) 
(list 3520.5459 871.2325) 
(list 3520.5459 871.2428) 
(list 3520.5459 871.2531) 
(list 3520.5459 871.2633) 
(list 3520.5459 871.2736) 
(list 3520.5459 871.2839) 
(list 3520.5459 871.2942) 
(list 3520.5459 871.3044) 
(list 3520.5459 871.3147) 
(list 3520.5459 871.325) 
(list 3520.5459 871.3353) 
(list 3520.5459 871.3456) 
(list 3520.5459 871.3558) 
(list 3520.5459 871.3661) 
(list 3520.5459 871.3764) 
(list 3520.5459 871.3867) 
(list 3520.5459 871.3969) 
(list 3520.5459 871.4072) 
(list 3520.5459 871.4175) 
(list 3520.5459 871.4278) 
(list 3520.5459 871.4381) 
(list 3520.5459 871.4483) 
(list 3520.5459 871.4586) 
(list 3520.5459 871.4689) 
(list 3520.5459 871.4792) 
(list 3520.5459 871.4894) 
(list 3520.5459 871.4997) 
(list 3520.5459 871.51) 
(list 3521.132 871.51)))
(apply 'command (append '("pline") coords '("c")))
(setq tap11 (ssadd (entlast) tap11))
(command "_mirror" (entlast) "" "3520,900" "3520,901" "No")
(setq tap11 (ssadd (entlast) tap11))
(setq coords (list 
(list 3520 871.51) 
(list 3520.135 871.51) 
(list 3520.135 871.5203) 
(list 3520.135 871.5306) 
(list 3520.135 871.5408) 
(list 3520.135 871.5511) 
(list 3520.135 871.5614) 
(list 3520.135 871.5717) 
(list 3520.135 871.5819) 
(list 3520.135 871.5922) 
(list 3520.135 871.6025) 
(list 3520.135 871.6128) 
(list 3520.135 871.6231) 
(list 3520.135 871.6333) 
(list 3520.135 871.6436) 
(list 3520.135 871.6539) 
(list 3520.135 871.6642) 
(list 3520.135 871.6744) 
(list 3520.135 871.6847) 
(list 3520.135 871.695) 
(list 3520.135 871.7053) 
(list 3520.135 871.7156) 
(list 3520.135 871.7258) 
(list 3520.135 871.7361) 
(list 3520.135 871.7464) 
(list 3520.135 871.7567) 
(list 3520.135 871.7669) 
(list 3520.135 871.7772) 
(list 3520.135 871.7875) 
(list 3520.135 871.7978) 
(list 3520.135 871.8081) 
(list 3520.135 871.8183) 
(list 3520.135 871.8286) 
(list 3520.135 871.8389) 
(list 3520.135 871.8492) 
(list 3520.135 871.8594) 
(list 3520.135 871.8697) 
(list 3520.135 871.88) 
(list 3520 871.88)))
(apply 'command (append '("pline") coords '("c")))
(setq tap11 (ssadd (entlast) tap11))
(command "_mirror" (entlast) "" "3520,900" "3520,901" "No")
(setq tap11 (ssadd (entlast) tap11))
(setq coords (list 
(list 3520.5559 871.51) 
(list 3520.5459 871.51) 
(list 3520.5444 871.5203) 
(list 3520.5393 871.5306) 
(list 3520.5309 871.5408) 
(list 3520.5194 871.5511) 
(list 3520.505 871.5614) 
(list 3520.4883 871.5717) 
(list 3520.4697 871.5819) 
(list 3520.4498 871.5922) 
(list 3520.4291 871.6025) 
(list 3520.4084 871.6128) 
(list 3520.3882 871.6231) 
(list 3520.3692 871.6333) 
(list 3520.352 871.6436) 
(list 3520.337 871.6539) 
(list 3520.3247 871.6642) 
(list 3520.3156 871.6744) 
(list 3520.31 871.6847) 
(list 3520.3079 871.695) 
(list 3520.3095 871.7053) 
(list 3520.3148 871.7156) 
(list 3520.3236 871.7258) 
(list 3520.3357 871.7361) 
(list 3520.3506 871.7464) 
(list 3520.3681 871.7567) 
(list 3520.3875 871.7669) 
(list 3520.4082 871.7772) 
(list 3520.4297 871.7875) 
(list 3520.4512 871.7978) 
(list 3520.4722 871.8081) 
(list 3520.492 871.8183) 
(list 3520.51 871.8286) 
(list 3520.5256 871.8389) 
(list 3520.5383 871.8492) 
(list 3520.5478 871.8594) 
(list 3520.5537 871.8697) 
(list 3520.5559 871.88) 
(list 3520.5559 871.88)))
(apply 'command (append '("pline") coords '("c")))
(setq tap11 (ssadd (entlast) tap11))
(command "_mirror" (entlast) "" "3520,900" "3520,901" "No")
(setq tap11 (ssadd (entlast) tap11))
(setq coords (list 
(list 3521.132 871.51) 
(list 3520.5559 871.51) 
(list 3520.5559 871.5203) 
(list 3520.5559 871.5306) 
(list 3520.5559 871.5408) 
(list 3520.5559 871.5511) 
(list 3520.5559 871.5614) 
(list 3520.5559 871.5717) 
(list 3520.5559 871.5819) 
(list 3520.5559 871.5922) 
(list 3520.5559 871.6025) 
(list 3520.5559 871.6128) 
(list 3520.5559 871.6231) 
(list 3520.5559 871.6333) 
(list 3520.5559 871.6436) 
(list 3520.5559 871.6539) 
(list 3520.5559 871.6642) 
(list 3520.5559 871.6744) 
(list 3520.5559 871.6847) 
(list 3520.5559 871.695) 
(list 3520.5559 871.7053) 
(list 3520.5559 871.7156) 
(list 3520.5559 871.7258) 
(list 3520.5559 871.7361) 
(list 3520.5559 871.7464) 
(list 3520.5559 871.7567) 
(list 3520.5559 871.7669) 
(list 3520.5559 871.7772) 
(list 3520.5559 871.7875) 
(list 3520.5559 871.7978) 
(list 3520.5559 871.8081) 
(list 3520.5559 871.8183) 
(list 3520.5559 871.8286) 
(list 3520.5559 871.8389) 
(list 3520.5559 871.8492) 
(list 3520.5559 871.8594) 
(list 3520.5559 871.8697) 
(list 3520.5559 871.88) 
(list 3521.132 871.88)))
(apply 'command (append '("pline") coords '("c")))
(setq tap11 (ssadd (entlast) tap11))
(command "_mirror" (entlast) "" "3520,900" "3520,901" "No")
(setq tap11 (ssadd (entlast) tap11))
(setq coords (list 
(list 3520 871.88) 
(list 3520.135 871.88) 
(list 3520.135 871.8903) 
(list 3520.135 871.9006) 
(list 3520.135 871.9108) 
(list 3520.135 871.9211) 
(list 3520.135 871.9314) 
(list 3520.135 871.9417) 
(list 3520.135 871.9519) 
(list 3520.135 871.9622) 
(list 3520.135 871.9725) 
(list 3520.135 871.9828) 
(list 3520.135 871.9931) 
(list 3520.135 872.0033) 
(list 3520.135 872.0136) 
(list 3520.135 872.0239) 
(list 3520.135 872.0342) 
(list 3520.135 872.0444) 
(list 3520.135 872.0547) 
(list 3520.135 872.065) 
(list 3520.135 872.0753) 
(list 3520.135 872.0856) 
(list 3520.135 872.0958) 
(list 3520.135 872.1061) 
(list 3520.135 872.1164) 
(list 3520.135 872.1267) 
(list 3520.135 872.1369) 
(list 3520.135 872.1472) 
(list 3520.135 872.1575) 
(list 3520.135 872.1678) 
(list 3520.135 872.1781) 
(list 3520.135 872.1883) 
(list 3520.135 872.1986) 
(list 3520.135 872.2089) 
(list 3520.135 872.2192) 
(list 3520.135 872.2294) 
(list 3520.135 872.2397) 
(list 3520.135 872.25) 
(list 3520 872.25)))
(apply 'command (append '("pline") coords '("c")))
(setq tap11 (ssadd (entlast) tap11))
(command "_mirror" (entlast) "" "3520,900" "3520,901" "No")
(setq tap11 (ssadd (entlast) tap11))
(setq coords (list 
(list 3520.566 871.88) 
(list 3520.5559 871.88) 
(list 3520.5543 871.8903) 
(list 3520.5489 871.9006) 
(list 3520.5398 871.9108) 
(list 3520.5273 871.9211) 
(list 3520.5119 871.9314) 
(list 3520.4939 871.9417) 
(list 3520.4738 871.9519) 
(list 3520.4524 871.9622) 
(list 3520.4302 871.9725) 
(list 3520.4079 871.9828) 
(list 3520.3862 871.9931) 
(list 3520.3658 872.0033) 
(list 3520.3472 872.0136) 
(list 3520.3311 872.0239) 
(list 3520.318 872.0342) 
(list 3520.3082 872.0444) 
(list 3520.3022 872.0547) 
(list 3520.3 872.065) 
(list 3520.3017 872.0753) 
(list 3520.3074 872.0856) 
(list 3520.3169 872.0958) 
(list 3520.3299 872.1061) 
(list 3520.3459 872.1164) 
(list 3520.3646 872.1267) 
(list 3520.3854 872.1369) 
(list 3520.4077 872.1472) 
(list 3520.4307 872.1575) 
(list 3520.4539 872.1678) 
(list 3520.4764 872.1781) 
(list 3520.4976 872.1883) 
(list 3520.5168 872.1986) 
(list 3520.5335 872.2089) 
(list 3520.5472 872.2192) 
(list 3520.5573 872.2294) 
(list 3520.5637 872.2397) 
(list 3520.566 872.25) 
(list 3520.566 872.25)))
(apply 'command (append '("pline") coords '("c")))
(setq tap11 (ssadd (entlast) tap11))
(command "_mirror" (entlast) "" "3520,900" "3520,901" "No")
(setq tap11 (ssadd (entlast) tap11))
(setq coords (list 
(list 3521.132 871.88) 
(list 3520.566 871.88) 
(list 3520.566 871.8903) 
(list 3520.566 871.9006) 
(list 3520.566 871.9108) 
(list 3520.566 871.9211) 
(list 3520.566 871.9314) 
(list 3520.566 871.9417) 
(list 3520.566 871.9519) 
(list 3520.566 871.9622) 
(list 3520.566 871.9725) 
(list 3520.566 871.9828) 
(list 3520.566 871.9931) 
(list 3520.566 872.0033) 
(list 3520.566 872.0136) 
(list 3520.566 872.0239) 
(list 3520.566 872.0342) 
(list 3520.566 872.0444) 
(list 3520.566 872.0547) 
(list 3520.566 872.065) 
(list 3520.566 872.0753) 
(list 3520.566 872.0856) 
(list 3520.566 872.0958) 
(list 3520.566 872.1061) 
(list 3520.566 872.1164) 
(list 3520.566 872.1267) 
(list 3520.566 872.1369) 
(list 3520.566 872.1472) 
(list 3520.566 872.1575) 
(list 3520.566 872.1678) 
(list 3520.566 872.1781) 
(list 3520.566 872.1883) 
(list 3520.566 872.1986) 
(list 3520.566 872.2089) 
(list 3520.566 872.2192) 
(list 3520.566 872.2294) 
(list 3520.566 872.2397) 
(list 3520.566 872.25) 
(list 3521.132 872.25)))
(apply 'command (append '("pline") coords '("c")))
(setq tap11 (ssadd (entlast) tap11))
(command "_mirror" (entlast) "" "3520,900" "3520,901" "No")
(setq tap11 (ssadd (entlast) tap11))
(command "_block" "blktap11" "3520,900" tap11 "")
(command "_insert" "blktap11" "3520,900" "1" "1" "0")
(command "_insert" "blktap11" "3520,900" "1" "1" "180")
(setq uc11 nil)
(setq uc11 (ssadd))
(setq coords (list 
(list 0 -0.185) 
(list 0.135 -0.185) 
(list 0.135 -0.17472) 
(list 0.135 -0.16444) 
(list 0.135 -0.15417) 
(list 0.135 -0.14389) 
(list 0.135 -0.13361) 
(list 0.135 -0.12333) 
(list 0.135 -0.11306) 
(list 0.135 -0.10278) 
(list 0.135 -0.0925) 
(list 0.135 -0.082222) 
(list 0.135 -0.071944) 
(list 0.135 -0.061667) 
(list 0.135 -0.051389) 
(list 0.135 -0.041111) 
(list 0.135 -0.030833) 
(list 0.135 -0.020556) 
(list 0.135 -0.010278) 
(list 0.135 0) 
(list 0.135 0.010278) 
(list 0.135 0.020556) 
(list 0.135 0.030833) 
(list 0.135 0.041111) 
(list 0.135 0.051389) 
(list 0.135 0.061667) 
(list 0.135 0.071944) 
(list 0.135 0.082222) 
(list 0.135 0.0925) 
(list 0.135 0.10278) 
(list 0.135 0.11306) 
(list 0.135 0.12333) 
(list 0.135 0.13361) 
(list 0.135 0.14389) 
(list 0.135 0.15417) 
(list 0.135 0.16444) 
(list 0.135 0.17472) 
(list 0.135 0.185) 
(list 0 0.185)))
(apply 'command (append '("pline") coords '("c")))
(setq uc11 (ssadd (entlast) uc11))
(setq coords (list 
(list 1.132 -0.185) 
(list 0.566 -0.185) 
(list 0.56395 -0.17472) 
(list 0.55786 -0.16444) 
(list 0.54791 -0.15417) 
(list 0.53442 -0.14389) 
(list 0.51778 -0.13361) 
(list 0.4985 -0.12333) 
(list 0.47717 -0.11306) 
(list 0.45444 -0.10278) 
(list 0.431 -0.0925) 
(list 0.40756 -0.082222) 
(list 0.38483 -0.071944) 
(list 0.3635 -0.061667) 
(list 0.34422 -0.051389) 
(list 0.32758 -0.041111) 
(list 0.31409 -0.030833) 
(list 0.30414 -0.020556) 
(list 0.29805 -0.010278) 
(list 0.296 0) 
(list 0.29805 0.010278) 
(list 0.30414 0.020556) 
(list 0.31409 0.030833) 
(list 0.32758 0.041111) 
(list 0.34422 0.051389) 
(list 0.3635 0.061667) 
(list 0.38483 0.071944) 
(list 0.40756 0.082222) 
(list 0.431 0.0925) 
(list 0.45444 0.10278) 
(list 0.47717 0.11306) 
(list 0.4985 0.12333) 
(list 0.51778 0.13361) 
(list 0.53442 0.14389) 
(list 0.54791 0.15417) 
(list 0.55786 0.16444) 
(list 0.56395 0.17472) 
(list 0.566 0.185) 
(list 1.132 0.185)))
(apply 'command (append '("pline") coords '("c")))
(setq uc11 (ssadd (entlast) uc11))
(command "_block" "blkuc11" "0,0.185" uc11 "")
(command "_insert" "blkuc11" "3520,872.62" "1" "1" "0")
(command "_insert" "blkuc11" "3520,872.25" "1" "1" "180")
(command "_insert" "blkuc11" "3520,872.99" "1" "1" "0")
(command "_insert" "blkuc11" "3520,872.62" "1" "1" "180")
(command "_insert" "blkuc11" "3520,873.36" "1" "1" "0")
(command "_insert" "blkuc11" "3520,872.99" "1" "1" "180")
(command "_insert" "blkuc11" "3520,873.73" "1" "1" "0")
(command "_insert" "blkuc11" "3520,873.36" "1" "1" "180")
(command "_insert" "blkuc11" "3520,874.1" "1" "1" "0")
(command "_insert" "blkuc11" "3520,873.73" "1" "1" "180")
(command "_insert" "blkuc11" "3520,874.47" "1" "1" "0")
(command "_insert" "blkuc11" "3520,874.1" "1" "1" "180")
(command "_insert" "blkuc11" "3520,874.84" "1" "1" "0")
(command "_insert" "blkuc11" "3520,874.47" "1" "1" "180")
(command "_insert" "blkuc11" "3520,875.21" "1" "1" "0")
(command "_insert" "blkuc11" "3520,874.84" "1" "1" "180")
(command "_insert" "blkuc11" "3520,875.58" "1" "1" "0")
(command "_insert" "blkuc11" "3520,875.21" "1" "1" "180")
(command "_insert" "blkuc11" "3520,875.95" "1" "1" "0")
(command "_insert" "blkuc11" "3520,875.58" "1" "1" "180")
(command "_insert" "blkuc11" "3520,876.32" "1" "1" "0")
(command "_insert" "blkuc11" "3520,875.95" "1" "1" "180")
(command "_insert" "blkuc11" "3520,876.69" "1" "1" "0")
(command "_insert" "blkuc11" "3520,876.32" "1" "1" "180")
(command "_insert" "blkuc11" "3520,877.06" "1" "1" "0")
(command "_insert" "blkuc11" "3520,876.69" "1" "1" "180")
(command "_insert" "blkuc11" "3520,877.43" "1" "1" "0")
(command "_insert" "blkuc11" "3520,877.06" "1" "1" "180")
(command "_insert" "blkuc11" "3520,877.8" "1" "1" "0")
(command "_insert" "blkuc11" "3520,877.43" "1" "1" "180")
(command "_insert" "blkuc11" "3520,878.17" "1" "1" "0")
(command "_insert" "blkuc11" "3520,877.8" "1" "1" "180")
(command "_insert" "blkuc11" "3520,878.54" "1" "1" "0")
(command "_insert" "blkuc11" "3520,878.17" "1" "1" "180")
(command "_insert" "blkuc11" "3520,878.91" "1" "1" "0")
(command "_insert" "blkuc11" "3520,878.54" "1" "1" "180")
(command "_insert" "blkuc11" "3520,879.28" "1" "1" "0")
(command "_insert" "blkuc11" "3520,878.91" "1" "1" "180")
(command "_insert" "blkuc11" "3520,879.65" "1" "1" "0")
(command "_insert" "blkuc11" "3520,879.28" "1" "1" "180")
(command "_insert" "blkuc11" "3520,880.02" "1" "1" "0")
(command "_insert" "blkuc11" "3520,879.65" "1" "1" "180")
(command "_insert" "blkuc11" "3520,880.39" "1" "1" "0")
(command "_insert" "blkuc11" "3520,880.02" "1" "1" "180")
(command "_insert" "blkuc11" "3520,880.76" "1" "1" "0")
(command "_insert" "blkuc11" "3520,880.39" "1" "1" "180")
(command "_insert" "blkuc11" "3520,881.13" "1" "1" "0")
(command "_insert" "blkuc11" "3520,880.76" "1" "1" "180")
(command "_insert" "blkuc11" "3520,881.5" "1" "1" "0")
(command "_insert" "blkuc11" "3520,881.13" "1" "1" "180")
(command "_insert" "blkuc11" "3520,881.87" "1" "1" "0")
(command "_insert" "blkuc11" "3520,881.5" "1" "1" "180")
(command "_insert" "blkuc11" "3520,882.24" "1" "1" "0")
(command "_insert" "blkuc11" "3520,881.87" "1" "1" "180")
(command "_insert" "blkuc11" "3520,882.61" "1" "1" "0")
(command "_insert" "blkuc11" "3520,882.24" "1" "1" "180")
(command "_insert" "blkuc11" "3520,882.98" "1" "1" "0")
(command "_insert" "blkuc11" "3520,882.61" "1" "1" "180")
(command "_insert" "blkuc11" "3520,883.35" "1" "1" "0")
(command "_insert" "blkuc11" "3520,882.98" "1" "1" "180")
(command "_insert" "blkuc11" "3520,883.72" "1" "1" "0")
(command "_insert" "blkuc11" "3520,883.35" "1" "1" "180")
(command "_insert" "blkuc11" "3520,884.09" "1" "1" "0")
(command "_insert" "blkuc11" "3520,883.72" "1" "1" "180")
(command "_insert" "blkuc11" "3520,884.46" "1" "1" "0")
(command "_insert" "blkuc11" "3520,884.09" "1" "1" "180")
(command "_insert" "blkuc11" "3520,884.83" "1" "1" "0")
(command "_insert" "blkuc11" "3520,884.46" "1" "1" "180")
(command "_insert" "blkuc11" "3520,885.2" "1" "1" "0")
(command "_insert" "blkuc11" "3520,884.83" "1" "1" "180")
(command "_insert" "blkuc11" "3520,885.57" "1" "1" "0")
(command "_insert" "blkuc11" "3520,885.2" "1" "1" "180")
(command "_insert" "blkuc11" "3520,885.94" "1" "1" "0")
(command "_insert" "blkuc11" "3520,885.57" "1" "1" "180")
(command "_insert" "blkuc11" "3520,886.31" "1" "1" "0")
(command "_insert" "blkuc11" "3520,885.94" "1" "1" "180")
(command "_insert" "blkuc11" "3520,886.68" "1" "1" "0")
(command "_insert" "blkuc11" "3520,886.31" "1" "1" "180")
(command "_insert" "blkuc11" "3520,887.05" "1" "1" "0")
(command "_insert" "blkuc11" "3520,886.68" "1" "1" "180")
(command "_insert" "blkuc11" "3520,887.42" "1" "1" "0")
(command "_insert" "blkuc11" "3520,887.05" "1" "1" "180")
(command "_insert" "blkuc11" "3520,887.79" "1" "1" "0")
(command "_insert" "blkuc11" "3520,887.42" "1" "1" "180")
(command "_insert" "blkuc11" "3520,888.16" "1" "1" "0")
(command "_insert" "blkuc11" "3520,887.79" "1" "1" "180")
(command "_insert" "blkuc11" "3520,888.53" "1" "1" "0")
(command "_insert" "blkuc11" "3520,888.16" "1" "1" "180")
(command "_insert" "blkuc11" "3520,888.9" "1" "1" "0")
(command "_insert" "blkuc11" "3520,888.53" "1" "1" "180")
(command "_insert" "blkuc11" "3520,889.27" "1" "1" "0")
(command "_insert" "blkuc11" "3520,888.9" "1" "1" "180")
(command "_insert" "blkuc11" "3520,889.64" "1" "1" "0")
(command "_insert" "blkuc11" "3520,889.27" "1" "1" "180")
(command "_insert" "blkuc11" "3520,890.01" "1" "1" "0")
(command "_insert" "blkuc11" "3520,889.64" "1" "1" "180")
(command "_insert" "blkuc11" "3520,890.38" "1" "1" "0")
(command "_insert" "blkuc11" "3520,890.01" "1" "1" "180")
(command "_insert" "blkuc11" "3520,890.75" "1" "1" "0")
(command "_insert" "blkuc11" "3520,890.38" "1" "1" "180")
(command "_insert" "blkuc11" "3520,891.12" "1" "1" "0")
(command "_insert" "blkuc11" "3520,890.75" "1" "1" "180")
(command "_insert" "blkuc11" "3520,891.49" "1" "1" "0")
(command "_insert" "blkuc11" "3520,891.12" "1" "1" "180")
(command "_insert" "blkuc11" "3520,891.86" "1" "1" "0")
(command "_insert" "blkuc11" "3520,891.49" "1" "1" "180")
(command "_insert" "blkuc11" "3520,892.23" "1" "1" "0")
(command "_insert" "blkuc11" "3520,891.86" "1" "1" "180")
(command "_insert" "blkuc11" "3520,892.6" "1" "1" "0")
(command "_insert" "blkuc11" "3520,892.23" "1" "1" "180")
(command "_insert" "blkuc11" "3520,892.97" "1" "1" "0")
(command "_insert" "blkuc11" "3520,892.6" "1" "1" "180")
(command "_insert" "blkuc11" "3520,893.34" "1" "1" "0")
(command "_insert" "blkuc11" "3520,892.97" "1" "1" "180")
(command "_insert" "blkuc11" "3520,893.71" "1" "1" "0")
(command "_insert" "blkuc11" "3520,893.34" "1" "1" "180")
(command "_insert" "blkuc11" "3520,894.08" "1" "1" "0")
(command "_insert" "blkuc11" "3520,893.71" "1" "1" "180")
(command "_insert" "blkuc11" "3520,894.45" "1" "1" "0")
(command "_insert" "blkuc11" "3520,894.08" "1" "1" "180")
(command "_insert" "blkuc11" "3520,894.82" "1" "1" "0")
(command "_insert" "blkuc11" "3520,894.45" "1" "1" "180")
(command "_insert" "blkuc11" "3520,895.19" "1" "1" "0")
(command "_insert" "blkuc11" "3520,894.82" "1" "1" "180")
(command "_insert" "blkuc11" "3520,895.56" "1" "1" "0")
(command "_insert" "blkuc11" "3520,895.19" "1" "1" "180")
(command "_insert" "blkuc11" "3520,895.93" "1" "1" "0")
(command "_insert" "blkuc11" "3520,895.56" "1" "1" "180")
(command "_insert" "blkuc11" "3520,896.3" "1" "1" "0")
(command "_insert" "blkuc11" "3520,895.93" "1" "1" "180")
(command "_insert" "blkuc11" "3520,896.67" "1" "1" "0")
(command "_insert" "blkuc11" "3520,896.3" "1" "1" "180")
(command "_insert" "blkuc11" "3520,897.04" "1" "1" "0")
(command "_insert" "blkuc11" "3520,896.67" "1" "1" "180")
(command "_insert" "blkuc11" "3520,897.41" "1" "1" "0")
(command "_insert" "blkuc11" "3520,897.04" "1" "1" "180")
(command "_insert" "blkuc11" "3520,897.78" "1" "1" "0")
(command "_insert" "blkuc11" "3520,897.41" "1" "1" "180")
(command "_insert" "blkuc11" "3520,898.15" "1" "1" "0")
(command "_insert" "blkuc11" "3520,897.78" "1" "1" "180")
(command "_insert" "blkuc11" "3520,898.52" "1" "1" "0")
(command "_insert" "blkuc11" "3520,898.15" "1" "1" "180")
(command "_insert" "blkuc11" "3520,898.89" "1" "1" "0")
(command "_insert" "blkuc11" "3520,898.52" "1" "1" "180")
(command "_insert" "blkuc11" "3520,899.26" "1" "1" "0")
(command "_insert" "blkuc11" "3520,898.89" "1" "1" "180")
(command "_insert" "blkuc11" "3520,899.63" "1" "1" "0")
(command "_insert" "blkuc11" "3520,899.26" "1" "1" "180")
(command "_insert" "blkuc11" "3520,900" "1" "1" "0")
(command "_insert" "blkuc11" "3520,899.63" "1" "1" "180")
(command "_insert" "blkuc11" "3520,900.37" "1" "1" "0")
(command "_insert" "blkuc11" "3520,900" "1" "1" "180")
(command "_insert" "blkuc11" "3520,900.74" "1" "1" "0")
(command "_insert" "blkuc11" "3520,900.37" "1" "1" "180")
(command "_insert" "blkuc11" "3520,901.11" "1" "1" "0")
(command "_insert" "blkuc11" "3520,900.74" "1" "1" "180")
(command "_insert" "blkuc11" "3520,901.48" "1" "1" "0")
(command "_insert" "blkuc11" "3520,901.11" "1" "1" "180")
(command "_insert" "blkuc11" "3520,901.85" "1" "1" "0")
(command "_insert" "blkuc11" "3520,901.48" "1" "1" "180")
(command "_insert" "blkuc11" "3520,902.22" "1" "1" "0")
(command "_insert" "blkuc11" "3520,901.85" "1" "1" "180")
(command "_insert" "blkuc11" "3520,902.59" "1" "1" "0")
(command "_insert" "blkuc11" "3520,902.22" "1" "1" "180")
(command "_insert" "blkuc11" "3520,902.96" "1" "1" "0")
(command "_insert" "blkuc11" "3520,902.59" "1" "1" "180")
(command "_insert" "blkuc11" "3520,903.33" "1" "1" "0")
(command "_insert" "blkuc11" "3520,902.96" "1" "1" "180")
(command "_insert" "blkuc11" "3520,903.7" "1" "1" "0")
(command "_insert" "blkuc11" "3520,903.33" "1" "1" "180")
(command "_insert" "blkuc11" "3520,904.07" "1" "1" "0")
(command "_insert" "blkuc11" "3520,903.7" "1" "1" "180")
(command "_insert" "blkuc11" "3520,904.44" "1" "1" "0")
(command "_insert" "blkuc11" "3520,904.07" "1" "1" "180")
(command "_insert" "blkuc11" "3520,904.81" "1" "1" "0")
(command "_insert" "blkuc11" "3520,904.44" "1" "1" "180")
(command "_insert" "blkuc11" "3520,905.18" "1" "1" "0")
(command "_insert" "blkuc11" "3520,904.81" "1" "1" "180")
(command "_insert" "blkuc11" "3520,905.55" "1" "1" "0")
(command "_insert" "blkuc11" "3520,905.18" "1" "1" "180")
(command "_insert" "blkuc11" "3520,905.92" "1" "1" "0")
(command "_insert" "blkuc11" "3520,905.55" "1" "1" "180")
(command "_insert" "blkuc11" "3520,906.29" "1" "1" "0")
(command "_insert" "blkuc11" "3520,905.92" "1" "1" "180")
(command "_insert" "blkuc11" "3520,906.66" "1" "1" "0")
(command "_insert" "blkuc11" "3520,906.29" "1" "1" "180")
(command "_insert" "blkuc11" "3520,907.03" "1" "1" "0")
(command "_insert" "blkuc11" "3520,906.66" "1" "1" "180")
(command "_insert" "blkuc11" "3520,907.4" "1" "1" "0")
(command "_insert" "blkuc11" "3520,907.03" "1" "1" "180")
(command "_insert" "blkuc11" "3520,907.77" "1" "1" "0")
(command "_insert" "blkuc11" "3520,907.4" "1" "1" "180")
(command "_insert" "blkuc11" "3520,908.14" "1" "1" "0")
(command "_insert" "blkuc11" "3520,907.77" "1" "1" "180")
(command "_insert" "blkuc11" "3520,908.51" "1" "1" "0")
(command "_insert" "blkuc11" "3520,908.14" "1" "1" "180")
(command "_insert" "blkuc11" "3520,908.88" "1" "1" "0")
(command "_insert" "blkuc11" "3520,908.51" "1" "1" "180")
(command "_insert" "blkuc11" "3520,909.25" "1" "1" "0")
(command "_insert" "blkuc11" "3520,908.88" "1" "1" "180")
(command "_insert" "blkuc11" "3520,909.62" "1" "1" "0")
(command "_insert" "blkuc11" "3520,909.25" "1" "1" "180")
(command "_insert" "blkuc11" "3520,909.99" "1" "1" "0")
(command "_insert" "blkuc11" "3520,909.62" "1" "1" "180")
(command "_insert" "blkuc11" "3520,910.36" "1" "1" "0")
(command "_insert" "blkuc11" "3520,909.99" "1" "1" "180")
(command "_insert" "blkuc11" "3520,910.73" "1" "1" "0")
(command "_insert" "blkuc11" "3520,910.36" "1" "1" "180")
(command "_insert" "blkuc11" "3520,911.1" "1" "1" "0")
(command "_insert" "blkuc11" "3520,910.73" "1" "1" "180")
(command "_insert" "blkuc11" "3520,911.47" "1" "1" "0")
(command "_insert" "blkuc11" "3520,911.1" "1" "1" "180")
(command "_insert" "blkuc11" "3520,911.84" "1" "1" "0")
(command "_insert" "blkuc11" "3520,911.47" "1" "1" "180")
(command "_insert" "blkuc11" "3520,912.21" "1" "1" "0")
(command "_insert" "blkuc11" "3520,911.84" "1" "1" "180")
(command "_insert" "blkuc11" "3520,912.58" "1" "1" "0")
(command "_insert" "blkuc11" "3520,912.21" "1" "1" "180")
(command "_insert" "blkuc11" "3520,912.95" "1" "1" "0")
(command "_insert" "blkuc11" "3520,912.58" "1" "1" "180")
(command "_insert" "blkuc11" "3520,913.32" "1" "1" "0")
(command "_insert" "blkuc11" "3520,912.95" "1" "1" "180")
(command "_insert" "blkuc11" "3520,913.69" "1" "1" "0")
(command "_insert" "blkuc11" "3520,913.32" "1" "1" "180")
(command "_insert" "blkuc11" "3520,914.06" "1" "1" "0")
(command "_insert" "blkuc11" "3520,913.69" "1" "1" "180")
(command "_insert" "blkuc11" "3520,914.43" "1" "1" "0")
(command "_insert" "blkuc11" "3520,914.06" "1" "1" "180")
(command "_insert" "blkuc11" "3520,914.8" "1" "1" "0")
(command "_insert" "blkuc11" "3520,914.43" "1" "1" "180")
(command "_insert" "blkuc11" "3520,915.17" "1" "1" "0")
(command "_insert" "blkuc11" "3520,914.8" "1" "1" "180")
(command "_insert" "blkuc11" "3520,915.54" "1" "1" "0")
(command "_insert" "blkuc11" "3520,915.17" "1" "1" "180")
(command "_insert" "blkuc11" "3520,915.91" "1" "1" "0")
(command "_insert" "blkuc11" "3520,915.54" "1" "1" "180")
(command "_insert" "blkuc11" "3520,916.28" "1" "1" "0")
(command "_insert" "blkuc11" "3520,915.91" "1" "1" "180")
(command "_insert" "blkuc11" "3520,916.65" "1" "1" "0")
(command "_insert" "blkuc11" "3520,916.28" "1" "1" "180")
(command "_insert" "blkuc11" "3520,917.02" "1" "1" "0")
(command "_insert" "blkuc11" "3520,916.65" "1" "1" "180")
(command "_insert" "blkuc11" "3520,917.39" "1" "1" "0")
(command "_insert" "blkuc11" "3520,917.02" "1" "1" "180")
(command "_insert" "blkuc11" "3520,917.76" "1" "1" "0")
(command "_insert" "blkuc11" "3520,917.39" "1" "1" "180")
(command "_insert" "blkuc11" "3520,918.13" "1" "1" "0")
(command "_insert" "blkuc11" "3520,917.76" "1" "1" "180")
(command "_insert" "blkuc11" "3520,918.5" "1" "1" "0")
(command "_insert" "blkuc11" "3520,918.13" "1" "1" "180")
(command "_insert" "blkuc11" "3520,918.87" "1" "1" "0")
(command "_insert" "blkuc11" "3520,918.5" "1" "1" "180")
(command "_insert" "blkuc11" "3520,919.24" "1" "1" "0")
(command "_insert" "blkuc11" "3520,918.87" "1" "1" "180")
(command "_insert" "blkuc11" "3520,919.61" "1" "1" "0")
(command "_insert" "blkuc11" "3520,919.24" "1" "1" "180")
(command "_insert" "blkuc11" "3520,919.98" "1" "1" "0")
(command "_insert" "blkuc11" "3520,919.61" "1" "1" "180")
(command "_insert" "blkuc11" "3520,920.35" "1" "1" "0")
(command "_insert" "blkuc11" "3520,919.98" "1" "1" "180")
(command "_insert" "blkuc11" "3520,920.72" "1" "1" "0")
(command "_insert" "blkuc11" "3520,920.35" "1" "1" "180")
(command "_insert" "blkuc11" "3520,921.09" "1" "1" "0")
(command "_insert" "blkuc11" "3520,920.72" "1" "1" "180")
(command "_insert" "blkuc11" "3520,921.46" "1" "1" "0")
(command "_insert" "blkuc11" "3520,921.09" "1" "1" "180")
(command "_insert" "blkuc11" "3520,921.83" "1" "1" "0")
(command "_insert" "blkuc11" "3520,921.46" "1" "1" "180")
(command "_insert" "blkuc11" "3520,922.2" "1" "1" "0")
(command "_insert" "blkuc11" "3520,921.83" "1" "1" "180")
(command "_insert" "blkuc11" "3520,922.57" "1" "1" "0")
(command "_insert" "blkuc11" "3520,922.2" "1" "1" "180")
(command "_insert" "blkuc11" "3520,922.94" "1" "1" "0")
(command "_insert" "blkuc11" "3520,922.57" "1" "1" "180")
(command "_insert" "blkuc11" "3520,923.31" "1" "1" "0")
(command "_insert" "blkuc11" "3520,922.94" "1" "1" "180")
(command "_insert" "blkuc11" "3520,923.68" "1" "1" "0")
(command "_insert" "blkuc11" "3520,923.31" "1" "1" "180")
(command "_insert" "blkuc11" "3520,924.05" "1" "1" "0")
(command "_insert" "blkuc11" "3520,923.68" "1" "1" "180")
(command "_insert" "blkuc11" "3520,924.42" "1" "1" "0")
(command "_insert" "blkuc11" "3520,924.05" "1" "1" "180")
(command "_insert" "blkuc11" "3520,924.79" "1" "1" "0")
(command "_insert" "blkuc11" "3520,924.42" "1" "1" "180")
(command "_insert" "blkuc11" "3520,925.16" "1" "1" "0")
(command "_insert" "blkuc11" "3520,924.79" "1" "1" "180")
(command "_insert" "blkuc11" "3520,925.53" "1" "1" "0")
(command "_insert" "blkuc11" "3520,925.16" "1" "1" "180")
(command "_insert" "blkuc11" "3520,925.9" "1" "1" "0")
(command "_insert" "blkuc11" "3520,925.53" "1" "1" "180")
(command "_insert" "blkuc11" "3520,926.27" "1" "1" "0")
(command "_insert" "blkuc11" "3520,925.9" "1" "1" "180")
(command "_insert" "blkuc11" "3520,926.64" "1" "1" "0")
(command "_insert" "blkuc11" "3520,926.27" "1" "1" "180")
(command "_insert" "blkuc11" "3520,927.01" "1" "1" "0")
(command "_insert" "blkuc11" "3520,926.64" "1" "1" "180")
(command "_insert" "blkuc11" "3520,927.38" "1" "1" "0")
(command "_insert" "blkuc11" "3520,927.01" "1" "1" "180")
(command "_insert" "blkuc11" "3520,927.75" "1" "1" "0")
(command "_insert" "blkuc11" "3520,927.38" "1" "1" "180")
(command "_layer" "set" "phccover" "")
(command "_rectangle" "3518.868,933.3" "3521.132,866.7")
(command "_layer" "set" "nitride" "")
(setq phc11 currobj)
(command "_layer" "set" "cover" "")
(command "_rectangle" "3518.868,836.7" "3521.132,963.3")
(command "_layer" "set" "nitride" "")
(command "_layer" "set" "text" "")
(command "_circle" "3517.918,846.7" "0.075")
(command "_circle" "3517.543,846.7" "0.15")
(command "_circle" "3517.168,846.7" "0.075")
(command "_circle" "3516.793,846.7" "0.15")
(command "_circle" "3517.918,848.7" "0.075")
(command "_circle" "3517.543,848.7" "0.075")
(command "_circle" "3517.168,848.7" "0.15")
(command "_circle" "3516.793,848.7" "0.15")
(command "_circle" "3517.918,850.7" "0.075")
(command "_circle" "3517.543,850.7" "0.15")
(command "_circle" "3517.168,850.7" "0.15")
(command "_circle" "3516.793,850.7" "0.15")
(command "_circle" "3517.918,852.7" "0.075")
(command "_circle" "3517.543,852.7" "0.075")
(command "_circle" "3517.168,852.7" "0.075")
(command "_circle" "3516.793,852.7" "0.075")
(command "_circle" "3516.418,852.7" "0.15")
(command "_circle" "3517.918,854.7" "0.075")
(command "_circle" "3517.543,854.7" "0.15")
(command "_circle" "3517.168,854.7" "0.075")
(command "_circle" "3516.793,854.7" "0.075")
(command "_circle" "3516.418,854.7" "0.15")
(command "_circle" "3517.918,856.7" "0.075")
(command "_circle" "3517.543,856.7" "0.075")
(command "_circle" "3517.168,856.7" "0.15")
(command "_circle" "3516.793,856.7" "0.075")
(command "_circle" "3516.418,856.7" "0.15")
(command "_circle" "3517.918,858.7" "0.075")
(command "_circle" "3517.543,858.7" "0.15")
(command "_circle" "3517.168,858.7" "0.15")
(command "_circle" "3516.793,858.7" "0.075")
(command "_circle" "3516.418,858.7" "0.15")
(command "_circle" "3517.918,860.7" "0.075")
(command "_circle" "3517.543,860.7" "0.075")
(command "_circle" "3517.168,860.7" "0.075")
(command "_circle" "3516.793,860.7" "0.15")
(command "_circle" "3516.418,860.7" "0.15")
(command "_circle" "3517.918,862.7" "0.075")
(command "_circle" "3517.543,862.7" "0.15")
(command "_circle" "3517.168,862.7" "0.075")
(command "_circle" "3516.793,862.7" "0.15")
(command "_circle" "3516.418,862.7" "0.15")
(command "_circle" "3517.918,864.7" "0.075")
(command "_circle" "3517.543,864.7" "0.075")
(command "_circle" "3517.168,864.7" "0.15")
(command "_circle" "3516.793,864.7" "0.15")
(command "_circle" "3516.418,864.7" "0.15")
(command "_circle" "3517.918,866.7" "0.075")
(command "_circle" "3517.543,866.7" "0.15")
(command "_circle" "3517.168,866.7" "0.15")
(command "_circle" "3516.793,866.7" "0.15")
(command "_circle" "3516.418,866.7" "0.15")
(command "_circle" "3517.918,868.7" "0.075")
(command "_circle" "3517.543,868.7" "0.075")
(command "_circle" "3517.168,868.7" "0.075")
(command "_circle" "3516.793,868.7" "0.075")
(command "_circle" "3516.418,868.7" "0.075")
(command "_circle" "3516.043,868.7" "0.15")
(command "_circle" "3517.918,870.7" "0.075")
(command "_circle" "3517.543,870.7" "0.15")
(command "_circle" "3517.168,870.7" "0.075")
(command "_circle" "3516.793,870.7" "0.075")
(command "_circle" "3516.418,870.7" "0.075")
(command "_circle" "3516.043,870.7" "0.15")
(command "_circle" "3517.918,872.7" "0.075")
(command "_circle" "3517.543,872.7" "0.075")
(command "_circle" "3517.168,872.7" "0.15")
(command "_circle" "3516.793,872.7" "0.075")
(command "_circle" "3516.418,872.7" "0.075")
(command "_circle" "3516.043,872.7" "0.15")
(command "_circle" "3517.918,874.7" "0.075")
(command "_circle" "3517.543,874.7" "0.15")
(command "_circle" "3517.168,874.7" "0.15")
(command "_circle" "3516.793,874.7" "0.075")
(command "_circle" "3516.418,874.7" "0.075")
(command "_circle" "3516.043,874.7" "0.15")
(command "_circle" "3517.918,876.7" "0.075")
(command "_circle" "3517.543,876.7" "0.075")
(command "_circle" "3517.168,876.7" "0.075")
(command "_circle" "3516.793,876.7" "0.15")
(command "_circle" "3516.418,876.7" "0.075")
(command "_circle" "3516.043,876.7" "0.15")
(command "_circle" "3517.918,878.7" "0.075")
(command "_circle" "3517.543,878.7" "0.15")
(command "_circle" "3517.168,878.7" "0.075")
(command "_circle" "3516.793,878.7" "0.15")
(command "_circle" "3516.418,878.7" "0.075")
(command "_circle" "3516.043,878.7" "0.15")
(command "_circle" "3517.918,880.7" "0.075")
(command "_circle" "3517.543,880.7" "0.075")
(command "_circle" "3517.168,880.7" "0.15")
(command "_circle" "3516.793,880.7" "0.15")
(command "_circle" "3516.418,880.7" "0.075")
(command "_circle" "3516.043,880.7" "0.15")
(command "_circle" "3517.918,882.7" "0.075")
(command "_circle" "3517.543,882.7" "0.15")
(command "_circle" "3517.168,882.7" "0.15")
(command "_circle" "3516.793,882.7" "0.15")
(command "_circle" "3516.418,882.7" "0.075")
(command "_circle" "3516.043,882.7" "0.15")
(command "_circle" "3517.918,884.7" "0.075")
(command "_circle" "3517.543,884.7" "0.075")
(command "_circle" "3517.168,884.7" "0.075")
(command "_circle" "3516.793,884.7" "0.075")
(command "_circle" "3516.418,884.7" "0.15")
(command "_circle" "3516.043,884.7" "0.15")
(command "_circle" "3517.918,886.7" "0.075")
(command "_circle" "3517.543,886.7" "0.15")
(command "_circle" "3517.168,886.7" "0.075")
(command "_circle" "3516.793,886.7" "0.075")
(command "_circle" "3516.418,886.7" "0.15")
(command "_circle" "3516.043,886.7" "0.15")
(command "_circle" "3517.918,888.7" "0.075")
(command "_circle" "3517.543,888.7" "0.075")
(command "_circle" "3517.168,888.7" "0.15")
(command "_circle" "3516.793,888.7" "0.075")
(command "_circle" "3516.418,888.7" "0.15")
(command "_circle" "3516.043,888.7" "0.15")
(command "_circle" "3517.918,890.7" "0.075")
(command "_circle" "3517.543,890.7" "0.15")
(command "_circle" "3517.168,890.7" "0.15")
(command "_circle" "3516.793,890.7" "0.075")
(command "_circle" "3516.418,890.7" "0.15")
(command "_circle" "3516.043,890.7" "0.15")
(command "_circle" "3517.918,892.7" "0.075")
(command "_circle" "3517.543,892.7" "0.075")
(command "_circle" "3517.168,892.7" "0.075")
(command "_circle" "3516.793,892.7" "0.15")
(command "_circle" "3516.418,892.7" "0.15")
(command "_circle" "3516.043,892.7" "0.15")
(command "_circle" "3517.918,894.7" "0.075")
(command "_circle" "3517.543,894.7" "0.15")
(command "_circle" "3517.168,894.7" "0.075")
(command "_circle" "3516.793,894.7" "0.15")
(command "_circle" "3516.418,894.7" "0.15")
(command "_circle" "3516.043,894.7" "0.15")
(command "_circle" "3517.918,896.7" "0.075")
(command "_circle" "3517.543,896.7" "0.075")
(command "_circle" "3517.168,896.7" "0.15")
(command "_circle" "3516.793,896.7" "0.15")
(command "_circle" "3516.418,896.7" "0.15")
(command "_circle" "3516.043,896.7" "0.15")
(command "_circle" "3517.918,898.7" "0.075")
(command "_circle" "3517.543,898.7" "0.15")
(command "_circle" "3517.168,898.7" "0.15")
(command "_circle" "3516.793,898.7" "0.15")
(command "_circle" "3516.418,898.7" "0.15")
(command "_circle" "3516.043,898.7" "0.15")
(command "_circle" "3517.918,900.7" "0.075")
(command "_circle" "3517.543,900.7" "0.075")
(command "_circle" "3517.168,900.7" "0.075")
(command "_circle" "3516.793,900.7" "0.075")
(command "_circle" "3516.418,900.7" "0.075")
(command "_circle" "3516.043,900.7" "0.075")
(command "_circle" "3515.668,900.7" "0.15")
(command "_circle" "3517.918,902.7" "0.075")
(command "_circle" "3517.543,902.7" "0.15")
(command "_circle" "3517.168,902.7" "0.075")
(command "_circle" "3516.793,902.7" "0.075")
(command "_circle" "3516.418,902.7" "0.075")
(command "_circle" "3516.043,902.7" "0.075")
(command "_circle" "3515.668,902.7" "0.15")
(command "_circle" "3517.918,904.7" "0.075")
(command "_circle" "3517.543,904.7" "0.075")
(command "_circle" "3517.168,904.7" "0.15")
(command "_circle" "3516.793,904.7" "0.075")
(command "_circle" "3516.418,904.7" "0.075")
(command "_circle" "3516.043,904.7" "0.075")
(command "_circle" "3515.668,904.7" "0.15")
(command "_circle" "3517.918,906.7" "0.075")
(command "_circle" "3517.543,906.7" "0.15")
(command "_circle" "3517.168,906.7" "0.15")
(command "_circle" "3516.793,906.7" "0.075")
(command "_circle" "3516.418,906.7" "0.075")
(command "_circle" "3516.043,906.7" "0.075")
(command "_circle" "3515.668,906.7" "0.15")
(command "_circle" "3517.918,908.7" "0.075")
(command "_circle" "3517.543,908.7" "0.075")
(command "_circle" "3517.168,908.7" "0.075")
(command "_circle" "3516.793,908.7" "0.15")
(command "_circle" "3516.418,908.7" "0.075")
(command "_circle" "3516.043,908.7" "0.075")
(command "_circle" "3515.668,908.7" "0.15")
(command "_circle" "3517.918,910.7" "0.075")
(command "_circle" "3517.543,910.7" "0.15")
(command "_circle" "3517.168,910.7" "0.075")
(command "_circle" "3516.793,910.7" "0.15")
(command "_circle" "3516.418,910.7" "0.075")
(command "_circle" "3516.043,910.7" "0.075")
(command "_circle" "3515.668,910.7" "0.15")
(command "_circle" "3517.918,912.7" "0.075")
(command "_circle" "3517.543,912.7" "0.075")
(command "_circle" "3517.168,912.7" "0.15")
(command "_circle" "3516.793,912.7" "0.15")
(command "_circle" "3516.418,912.7" "0.075")
(command "_circle" "3516.043,912.7" "0.075")
(command "_circle" "3515.668,912.7" "0.15")
(command "_circle" "3517.918,914.7" "0.075")
(command "_circle" "3517.543,914.7" "0.15")
(command "_circle" "3517.168,914.7" "0.15")
(command "_circle" "3516.793,914.7" "0.15")
(command "_circle" "3516.418,914.7" "0.075")
(command "_circle" "3516.043,914.7" "0.075")
(command "_circle" "3515.668,914.7" "0.15")
(command "_circle" "3517.918,916.7" "0.075")
(command "_circle" "3517.543,916.7" "0.075")
(command "_circle" "3517.168,916.7" "0.075")
(command "_circle" "3516.793,916.7" "0.075")
(command "_circle" "3516.418,916.7" "0.15")
(command "_circle" "3516.043,916.7" "0.075")
(command "_circle" "3515.668,916.7" "0.15")
(command "_circle" "3517.918,918.7" "0.075")
(command "_circle" "3517.543,918.7" "0.15")
(command "_circle" "3517.168,918.7" "0.075")
(command "_circle" "3516.793,918.7" "0.075")
(command "_circle" "3516.418,918.7" "0.15")
(command "_circle" "3516.043,918.7" "0.075")
(command "_circle" "3515.668,918.7" "0.15")
(command "_circle" "3517.918,920.7" "0.075")
(command "_circle" "3517.543,920.7" "0.075")
(command "_circle" "3517.168,920.7" "0.15")
(command "_circle" "3516.793,920.7" "0.075")
(command "_circle" "3516.418,920.7" "0.15")
(command "_circle" "3516.043,920.7" "0.075")
(command "_circle" "3515.668,920.7" "0.15")
(command "_circle" "3517.918,922.7" "0.075")
(command "_circle" "3517.543,922.7" "0.15")
(command "_circle" "3517.168,922.7" "0.15")
(command "_circle" "3516.793,922.7" "0.075")
(command "_circle" "3516.418,922.7" "0.15")
(command "_circle" "3516.043,922.7" "0.075")
(command "_circle" "3515.668,922.7" "0.15")
(command "_circle" "3517.918,924.7" "0.075")
(command "_circle" "3517.543,924.7" "0.075")
(command "_circle" "3517.168,924.7" "0.075")
(command "_circle" "3516.793,924.7" "0.15")
(command "_circle" "3516.418,924.7" "0.15")
(command "_circle" "3516.043,924.7" "0.075")
(command "_circle" "3515.668,924.7" "0.15")
(command "_circle" "3517.918,926.7" "0.075")
(command "_circle" "3517.543,926.7" "0.15")
(command "_circle" "3517.168,926.7" "0.075")
(command "_circle" "3516.793,926.7" "0.15")
(command "_circle" "3516.418,926.7" "0.15")
(command "_circle" "3516.043,926.7" "0.075")
(command "_circle" "3515.668,926.7" "0.15")
(command "_circle" "3517.918,928.7" "0.075")
(command "_circle" "3517.543,928.7" "0.075")
(command "_circle" "3517.168,928.7" "0.15")
(command "_circle" "3516.793,928.7" "0.15")
(command "_circle" "3516.418,928.7" "0.15")
(command "_circle" "3516.043,928.7" "0.075")
(command "_circle" "3515.668,928.7" "0.15")
(command "_circle" "3517.918,930.7" "0.075")
(command "_circle" "3517.543,930.7" "0.15")
(command "_circle" "3517.168,930.7" "0.15")
(command "_circle" "3516.793,930.7" "0.15")
(command "_circle" "3516.418,930.7" "0.15")
(command "_circle" "3516.043,930.7" "0.075")
(command "_circle" "3515.668,930.7" "0.15")
(command "_circle" "3517.918,932.7" "0.075")
(command "_circle" "3517.543,932.7" "0.075")
(command "_circle" "3517.168,932.7" "0.075")
(command "_circle" "3516.793,932.7" "0.075")
(command "_circle" "3516.418,932.7" "0.075")
(command "_circle" "3516.043,932.7" "0.15")
(command "_circle" "3515.668,932.7" "0.15")
(command "_circle" "3517.918,934.7" "0.075")
(command "_circle" "3517.543,934.7" "0.15")
(command "_circle" "3517.168,934.7" "0.075")
(command "_circle" "3516.793,934.7" "0.075")
(command "_circle" "3516.418,934.7" "0.075")
(command "_circle" "3516.043,934.7" "0.15")
(command "_circle" "3515.668,934.7" "0.15")
(command "_circle" "3517.918,936.7" "0.075")
(command "_circle" "3517.543,936.7" "0.075")
(command "_circle" "3517.168,936.7" "0.15")
(command "_circle" "3516.793,936.7" "0.075")
(command "_circle" "3516.418,936.7" "0.075")
(command "_circle" "3516.043,936.7" "0.15")
(command "_circle" "3515.668,936.7" "0.15")
(command "_circle" "3517.918,938.7" "0.075")
(command "_circle" "3517.543,938.7" "0.15")
(command "_circle" "3517.168,938.7" "0.15")
(command "_circle" "3516.793,938.7" "0.075")
(command "_circle" "3516.418,938.7" "0.075")
(command "_circle" "3516.043,938.7" "0.15")
(command "_circle" "3515.668,938.7" "0.15")
(command "_circle" "3517.918,940.7" "0.075")
(command "_circle" "3517.543,940.7" "0.075")
(command "_circle" "3517.168,940.7" "0.075")
(command "_circle" "3516.793,940.7" "0.15")
(command "_circle" "3516.418,940.7" "0.075")
(command "_circle" "3516.043,940.7" "0.15")
(command "_circle" "3515.668,940.7" "0.15")
(command "_circle" "3517.918,942.7" "0.075")
(command "_circle" "3517.543,942.7" "0.15")
(command "_circle" "3517.168,942.7" "0.075")
(command "_circle" "3516.793,942.7" "0.15")
(command "_circle" "3516.418,942.7" "0.075")
(command "_circle" "3516.043,942.7" "0.15")
(command "_circle" "3515.668,942.7" "0.15")
(command "_circle" "3517.918,944.7" "0.075")
(command "_circle" "3517.543,944.7" "0.075")
(command "_circle" "3517.168,944.7" "0.15")
(command "_circle" "3516.793,944.7" "0.15")
(command "_circle" "3516.418,944.7" "0.075")
(command "_circle" "3516.043,944.7" "0.15")
(command "_circle" "3515.668,944.7" "0.15")
(command "_circle" "3517.918,946.7" "0.075")
(command "_circle" "3517.543,946.7" "0.15")
(command "_circle" "3517.168,946.7" "0.15")
(command "_circle" "3516.793,946.7" "0.15")
(command "_circle" "3516.418,946.7" "0.075")
(command "_circle" "3516.043,946.7" "0.15")
(command "_circle" "3515.668,946.7" "0.15")
(command "_circle" "3517.918,948.7" "0.075")
(command "_circle" "3517.543,948.7" "0.075")
(command "_circle" "3517.168,948.7" "0.075")
(command "_circle" "3516.793,948.7" "0.075")
(command "_circle" "3516.418,948.7" "0.15")
(command "_circle" "3516.043,948.7" "0.15")
(command "_circle" "3515.668,948.7" "0.15")
(command "_circle" "3517.918,950.7" "0.075")
(command "_circle" "3517.543,950.7" "0.15")
(command "_circle" "3517.168,950.7" "0.075")
(command "_circle" "3516.793,950.7" "0.075")
(command "_circle" "3516.418,950.7" "0.15")
(command "_circle" "3516.043,950.7" "0.15")
(command "_circle" "3515.668,950.7" "0.15")
(command "_circle" "3517.918,952.7" "0.075")
(command "_circle" "3517.543,952.7" "0.075")
(command "_circle" "3517.168,952.7" "0.15")
(command "_circle" "3516.793,952.7" "0.075")
(command "_circle" "3516.418,952.7" "0.15")
(command "_circle" "3516.043,952.7" "0.15")
(command "_circle" "3515.668,952.7" "0.15")
(command "_circle" "3517.918,954.7" "0.075")
(command "_circle" "3517.543,954.7" "0.15")
(command "_circle" "3517.168,954.7" "0.15")
(command "_circle" "3516.793,954.7" "0.075")
(command "_circle" "3516.418,954.7" "0.15")
(command "_circle" "3516.043,954.7" "0.15")
(command "_circle" "3515.668,954.7" "0.15")
(command "_circle" "3517.918,956.7" "0.075")
(command "_circle" "3517.543,956.7" "0.075")
(command "_circle" "3517.168,956.7" "0.075")
(command "_circle" "3516.793,956.7" "0.15")
(command "_circle" "3516.418,956.7" "0.15")
(command "_circle" "3516.043,956.7" "0.15")
(command "_circle" "3515.668,956.7" "0.15")
(command "_circle" "3517.918,958.7" "0.075")
(command "_circle" "3517.543,958.7" "0.15")
(command "_circle" "3517.168,958.7" "0.075")
(command "_circle" "3516.793,958.7" "0.15")
(command "_circle" "3516.418,958.7" "0.15")
(command "_circle" "3516.043,958.7" "0.15")
(command "_circle" "3515.668,958.7" "0.15")
(command "_circle" "3517.918,960.7" "0.075")
(command "_circle" "3517.543,960.7" "0.075")
(command "_circle" "3517.168,960.7" "0.15")
(command "_circle" "3516.793,960.7" "0.15")
(command "_circle" "3516.418,960.7" "0.15")
(command "_circle" "3516.043,960.7" "0.15")
(command "_circle" "3515.668,960.7" "0.15")
(command "_circle" "3517.918,962.7" "0.075")
(command "_circle" "3517.543,962.7" "0.15")
(command "_circle" "3517.168,962.7" "0.15")
(command "_circle" "3516.793,962.7" "0.15")
(command "_circle" "3516.418,962.7" "0.15")
(command "_circle" "3516.043,962.7" "0.15")
(command "_circle" "3515.668,962.7" "0.15")
(command "_layer" "set" "nitride" "")
(command "_layer" "set" "text" "")
(command-s "_text" "3506.868,963.3" "2" "-90" "a = 370 nm" )
(sssetfirst nil (ssget "_L"))
(if (not (numberp (vl-string-search "Mac" (getvar "platform")))) (c:txtexp))
(command "_layer" "set" "nitride" "")
(command "_layer" "set" "text" "")
(command-s "_text" "3503.868,963.3" "2" "-90" "gap = 270 nm" )
(sssetfirst nil (ssget "_L"))
(if (not (numberp (vl-string-search "Mac" (getvar "platform")))) (c:txtexp))
(command "_layer" "set" "nitride" "")
(command "_layer" "set" "text" "")
(command-s "_text" "3500.868,963.3" "2" "-90" "amplitude = 135 nm" )
(sssetfirst nil (ssget "_L"))
(if (not (numberp (vl-string-search "Mac" (getvar "platform")))) (c:txtexp))
(command "_layer" "set" "nitride" "")
(command "_layer" "set" "text" "")
(command-s "_text" "3497.868,963.3" "2" "-90" "start width = 280 nm" )
(sssetfirst nil (ssget "_L"))
(if (not (numberp (vl-string-search "Mac" (getvar "platform")))) (c:txtexp))
(command "_layer" "set" "nitride" "")
(command "_layer" "set" "text" "")
(command-s "_text" "3494.868,963.3" "2" "-90" "width = 296 nm" )
(sssetfirst nil (ssget "_L"))
(if (not (numberp (vl-string-search "Mac" (getvar "platform")))) (c:txtexp))
(command "_layer" "set" "nitride" "")
(command "_layer" "set" "text" "")
(command-s "_text" "3491.868,963.3" "2" "-90" "taper: 15" )
(sssetfirst nil (ssget "_L"))
(if (not (numberp (vl-string-search "Mac" (getvar "platform")))) (c:txtexp))
(command "_layer" "set" "nitride" "")
(command "_layer" "set" "text" "")
(command-s "_text" "3488.868,963.3" "2" "-90" "nominal: 150" )
(sssetfirst nil (ssget "_L"))
(if (not (numberp (vl-string-search "Mac" (getvar "platform")))) (c:txtexp))
(command "_layer" "set" "nitride" "")
(command "_layer" "set" "indicators" "")
(setq coords (list 
(list 3440.415 940) 
(list 3440.415 920) 
(list 3420.415 900) 
(list 3440.415 880) 
(list 3440.415 860) 
(list 3440.415 900) 
(list 3440.415 887.0711) 
(list 3427.4861 900) 
(list 3440.415 912.9289) 
(list 3440.415 900)))
(apply 'command (append '("pline") coords '("c")))
(command "._fillet" "radius" "1" "._fillet" "P" (entlast))
(setq coords (list 
(list 3599.585 940) 
(list 3599.585 920) 
(list 3619.585 900) 
(list 3599.585 880) 
(list 3599.585 860) 
(list 3599.585 900) 
(list 3599.585 887.0711) 
(list 3612.5139 900) 
(list 3599.585 912.9289) 
(list 3599.585 900)))
(apply 'command (append '("pline") coords '("c")))
(command "._fillet" "radius" "1" "._fillet" "P" (entlast))
(command "_layer" "set" "holes" "")
(command "_circle" "3438.0629,914.1124" "0.5")
(command "_circle" "3435.7109,911.7603" "0.5")
(command "_circle" "3433.3588,909.4083" "0.5")
(command "_circle" "3431.0067,907.0562" "0.5")
(command "_circle" "3428.6547,904.7041" "0.5")
(command "_circle" "3426.3026,902.3521" "0.5")
(command "_circle" "3423.9505,900" "0.5")
(command "_circle" "3426.3026,897.6479" "0.5")
(command "_circle" "3428.6547,895.2959" "0.5")
(command "_circle" "3431.0067,892.9438" "0.5")
(command "_circle" "3433.3588,890.5917" "0.5")
(command "_circle" "3435.7109,888.2397" "0.5")
(command "_circle" "3438.0629,885.8876" "0.5")
(command "_circle" "3601.9371,914.1124" "0.5")
(command "_circle" "3604.2891,911.7603" "0.5")
(command "_circle" "3606.6412,909.4083" "0.5")
(command "_circle" "3608.9933,907.0562" "0.5")
(command "_circle" "3611.3453,904.7041" "0.5")
(command "_circle" "3613.6974,902.3521" "0.5")
(command "_circle" "3616.0495,900" "0.5")
(command "_circle" "3613.6974,897.6479" "0.5")
(command "_circle" "3611.3453,895.2959" "0.5")
(command "_circle" "3608.9933,892.9438" "0.5")
(command "_circle" "3606.6412,890.5917" "0.5")
(command "_circle" "3604.2891,888.2397" "0.5")
(command "_circle" "3601.9371,885.8876" "0.5")
(command "_layer" "set" "nitride" "")
(command "_block" "blkcoupler11" "3520,900" coupler11 "")
(command "_insert" "blkcoupler11" "3520,900" "1" "1" "0")
(command "_insert" "blkcoupler11" "3520,900" "1" "1" "180")
(command "_block" "blksinglenanobeam11" "3520,900" singlenanobeam11 "")
(command "_insert" "blksinglenanobeam11" "3520,900" "1" "1" "0")
(command "_insert" "blksinglenanobeam11" "3520,900" "1" "1" "180")
(command "_block" "blkanglednodearray11" "3520,900" anglednodearray11 "")
(command "_insert" "blkanglednodearray11" "3520,900" "1" "1" "0")
(command "_insert" "blkanglednodearray11" "3520,900" "1" "1" "180")
(command "_block" "blkcooledsinglenanobeam11" "3520,900" cooledsinglenanobeam11 "")
(command "_insert" "blkcooledsinglenanobeam11" "3520,900" "1" "1" "0")
(command "_insert" "blkcooledsinglenanobeam11" "3520,900" "1" "1" "180")
(command "_block" "blkyjunction11" "3520,900" yjunction11 "")
(command "_insert" "blkyjunction11" "3520,900" "1" "1" "0")
(command "_insert" "blkyjunction11" "3520,900" "1" "1" "180")
; DRAWING BULGING VEE GROOVE
(command "_layer" "set" "vgroove" "")
(setq coords (list 
(list 3445.415 -605) 
(list 3445.415 0) 
(list 3445.415 0) 
(list 3445.415 1800) 
(list 3445.415 1800) 
(list 3445.415 2405) 
(list 3594.585 2405) 
(list 3594.585 1800) 
(list 3594.585 1800) 
(list 3594.585 0) 
(list 3594.585 0) 
(list 3594.585 -605)))
(apply 'command (append '("pline") coords '("c")))
(command "._fillet" "radius" "0" "._fillet" "P" (entlast))
(command "_layer" "set" "window" "")
(command "_rectangle" "3445.415,-1935" "3594.585,-600")
(command "_rectangle" "3445.415,2400" "3594.585,5300")
(command "_layer" "set" "grid" "")
(command "_rectangle" "3446.415,-1934" "3469.9433,-1909.2133")
(command "_array" "last" "" "R" "75" "3" "25.7867" "24.5283")
(command "_rectangle" "3521,-1934" "3544.5283,-1909.2133")
(command "_array" "last" "" "R" "75" "3" "25.7867" "24.5283")
(command "_rectangle" "3446.415,1" "3469.9433,25.7")
(command "_array" "last" "" "R" "70" "3" "25.7" "24.5283")
(command "_rectangle" "3521,1" "3544.5283,25.7")
(command "_array" "last" "" "R" "70" "3" "25.7" "24.5283")
(command "_rectangle" "3446.415,1801" "3469.9433,1825.9185")
(command "_array" "last" "" "R" "135" "3" "25.9185" "24.5283")
(command "_rectangle" "3521,1801" "3544.5283,1825.9185")
(command "_array" "last" "" "R" "135" "3" "25.9185" "24.5283")
(command "_layer" "set" "vgrooveFDA" "")
(command "_rectangle" "3594.585,-2233" "3445.415,-1933")
(command "_layer" "set" "nitride" "")
(command "_layer" "set" "holes" "")
(command "_circle" "3597.085,331.5" "0.5")
(command "_array" "last" "" "R" "379" "1" "3" "2.5")
(command "_circle" "3442.915,331.5" "0.5")
(command "_array" "last" "" "R" "379" "1" "3" "-2.5")
(command "_layer" "set" "nitride" "")
(command "_layer" "set" "window" "")
(command "_layer" "set" "window" "")
(command "_rectangle" "3599.585,0" "3760.415,1800")
(command "._fillet" "radius" "20" "._fillet" "P" (entlast))
(command "_layer" "set" "grid" "")
(command "_rectangle" "3600.585,1" "3622.4179,25.7")
(command "_array" "last" "" "R" "70" "7" "25.7" "22.8329")
(command "_layer" "set" "nitride" "")
; DRAWING REGION LAYER
(command "_layer" "set" "regionLayer11" "")
(command "_rectangle" "3440,-460" "3600,2260")
(command "_layer" "set" "nitride" "")
(setq coupler11 nil)
(setq singlenanobeam11 nil)
(setq anglednodearray11 nil)
(setq cooledsinglenanobeam11 nil)
(setq yjunction11 nil)
; DEVICE #12
(command "_layer" "set" "window" "")
(command "_circle" "3752.915,-415" "5")
(command "_circle" "3752.915,-402.5" "5")
(command "_circle" "3752.915,-390" "5")
(command "_circle" "3752.915,-377.5" "5")
(command "_circle" "3740.415,-415" "5")
(command "_circle" "3740.415,-402.5" "5")
(command "_circle" "3740.415,-390" "5")
(command "_circle" "3740.415,-377.5" "5")
(command "_circle" "3727.915,-415" "5")
(command "_circle" "3727.915,-402.5" "5")
(command "_circle" "3727.915,-390" "5")
(command "_circle" "3727.915,-377.5" "5")
(command "_layer" "set" "nitride" "")
(setq currobj nil)
(setq currobj (ssadd))
; DRAWING COUPLER
(setq coords (list 
(list 3840.0645 -415) 
(list 3840.0645 -413) 
(list 3913.585 -413) 
(list 3913.585 -413) 
(list 3913.9677 -413.0761) 
(list 3914.2921 -413.2929) 
(list 3914.5089 -413.6173) 
(list 3914.585 -414) 
(list 3914.585 -411.8) 
(list 3914.585 -411.8) 
(list 3914.5089 -412.1827) 
(list 3914.2921 -412.5071) 
(list 3913.9677 -412.7239) 
(list 3913.585 -412.8) 
(list 3840.0645 -412.8) 
(list 3840.0645 -410.8) 
(list 3839.9355 -410.8) 
(list 3839.9355 -412.8) 
(list 3766.415 -412.8) 
(list 3766.0323 -412.7239) 
(list 3765.7079 -412.5071) 
(list 3765.4911 -412.1827) 
(list 3765.415 -411.8) 
(list 3765.415 -411.8) 
(list 3765.415 -414) 
(list 3765.4911 -413.6173) 
(list 3765.7079 -413.2929) 
(list 3766.0323 -413.0761) 
(list 3766.415 -413) 
(list 3766.415 -413) 
(list 3839.9355 -413) 
(list 3839.9355 -415)))
(apply 'command (append '("pline") coords '("c")))
(setq currobj (ssadd (entlast) currobj))
(command "._fillet" "radius" "0.3" "._fillet" "P" (entlast))
(command "_layer" "set" "holes" "")
(command "_circle" "3840,-412.9" "0.113")
(setq currobj (ssadd (entlast) currobj))
(command "_layer" "set" "nitride" "")
(command "_layer" "set" "text" "")
(command "_circle" "3839.2,-415" "0.075")
(command "_circle" "3839.2,-414.7" "0.075")
(command "_circle" "3839.2,-414.4" "0.075")
(command "_circle" "3838.9,-415" "0.075")
(command "_circle" "3838.9,-414.7" "0.075")
(command "_circle" "3838.9,-414.4" "0.075")
(command "_circle" "3838.6,-415" "0.075")
(command "_circle" "3838.6,-414.7" "0.075")
(command "_circle" "3838.6,-414.4" "0.075")
(command "_layer" "set" "nitride" "")
(command "_layer" "set" "prebias" "")
(command "_rectangle" "3765.415,-414" "3914.585,-411.8")
(setq currobj (ssadd (entlast) currobj))
(command "_rectangle" "3839.9355,-415" "3840.0645,-410.8")
(setq currobj (ssadd (entlast) currobj))
(command "_layer" "set" "nitride" "")
(setq coupler12 currobj)
(setq currobj nil)
(setq currobj (ssadd))
; DRAWING SINGLE NANOBEAM
(setq coords (list 
(list 3840.0645 -410.8) 
(list 3840.0645 -409.1417) 
(list 3840.0645 -407.4833) 
(list 3840.0645 -405.825) 
(list 3840.0645 -404.1667) 
(list 3840.0645 -402.5083) 
(list 3840.0645 -400.85) 
(list 3840.0645 -399.1917) 
(list 3840.0645 -397.5333) 
(list 3840.0646 -395.875) 
(list 3840.0646 -394.2167) 
(list 3840.0646 -392.5583) 
(list 3840.0646 -390.9) 
(list 3840.0647 -389.2417) 
(list 3840.0647 -387.5833) 
(list 3840.0647 -385.925) 
(list 3840.0648 -384.2667) 
(list 3840.0648 -382.6083) 
(list 3840.0649 -380.95) 
(list 3840.065 -379.2917) 
(list 3840.0651 -377.6333) 
(list 3840.0651 -375.975) 
(list 3840.0652 -374.3167) 
(list 3840.0653 -372.6583) 
(list 3840.0655 -371) 
(list 3840.0656 -369.3417) 
(list 3840.0657 -367.6833) 
(list 3840.0659 -366.025) 
(list 3840.066 -364.3667) 
(list 3840.0662 -362.7083) 
(list 3840.0664 -361.05) 
(list 3840.0666 -359.3917) 
(list 3840.0668 -357.7333) 
(list 3840.067 -356.075) 
(list 3840.0672 -354.4167) 
(list 3840.0675 -352.7583) 
(list 3840.0678 -351.1) 
(list 3840.068 -349.4417) 
(list 3840.0683 -347.7833) 
(list 3840.0686 -346.125) 
(list 3840.069 -344.4667) 
(list 3840.0693 -342.8083) 
(list 3840.0697 -341.15) 
(list 3840.07 -339.4917) 
(list 3840.0704 -337.8333) 
(list 3840.0709 -336.175) 
(list 3840.0713 -334.5167) 
(list 3840.0717 -332.8583) 
(list 3840.0722 -331.2) 
(list 3840.0727 -329.5417) 
(list 3840.0732 -327.8833) 
(list 3840.0738 -326.225) 
(list 3840.0743 -324.5667) 
(list 3840.0749 -322.9083) 
(list 3840.0755 -321.25) 
(list 3840.0761 -319.5917) 
(list 3840.0767 -317.9333) 
(list 3840.0774 -316.275) 
(list 3840.0781 -314.6167) 
(list 3840.0788 -312.9583) 
(list 3840.0796 -311.3) 
(list 3840.0803 -309.6417) 
(list 3840.0811 -307.9833) 
(list 3840.0819 -306.325) 
(list 3840.0828 -304.6667) 
(list 3840.0837 -303.0083) 
(list 3840.0845 -301.35) 
(list 3840.0855 -299.6917) 
(list 3840.0864 -298.0333) 
(list 3840.0874 -296.375) 
(list 3840.0884 -294.7167) 
(list 3840.0895 -293.0583) 
(list 3840.0905 -291.4) 
(list 3840.0916 -289.7417) 
(list 3840.0928 -288.0833) 
(list 3840.0939 -286.425) 
(list 3840.0951 -284.7667) 
(list 3840.0963 -283.1083) 
(list 3840.0976 -281.45) 
(list 3840.0989 -279.7917) 
(list 3840.1002 -278.1333) 
(list 3840.1016 -276.475) 
(list 3840.1029 -274.8167) 
(list 3840.1044 -273.1583) 
(list 3840.1058 -271.5) 
(list 3840.1073 -269.8417) 
(list 3840.1089 -268.1833) 
(list 3840.1104 -266.525) 
(list 3840.112 -264.8667) 
(list 3840.1137 -263.2083) 
(list 3840.1153 -261.55) 
(list 3840.117 -259.8917) 
(list 3840.1188 -258.2333) 
(list 3840.1206 -256.575) 
(list 3840.1224 -254.9167) 
(list 3840.1243 -253.2583) 
(list 3840.1262 -251.6) 
(list 3840.1281 -249.9417) 
(list 3840.1301 -248.2833) 
(list 3840.1322 -246.625) 
(list 3840.1342 -244.9667) 
(list 3840.1363 -243.3083) 
(list 3840.1385 -241.65) 
(list 3840.1407 -239.9917) 
(list 3840.1429 -238.3333) 
(list 3840.1452 -236.675) 
(list 3840.1476 -235.0167) 
(list 3840.1499 -233.3583) 
(list 3840.1523 -231.7) 
(list 3840.1548 -230.0417) 
(list 3840.1573 -228.3833) 
(list 3840.1599 -226.725) 
(list 3840.1625 -225.0667) 
(list 3840.1651 -223.4083) 
(list 3840.1678 -221.75) 
(list 3840.1706 -220.0917) 
(list 3840.1733 -218.4333) 
(list 3840.1762 -216.775) 
(list 3840.1791 -215.1167) 
(list 3840.182 -213.4583) 
(list 3840.185 -211.8) 
(list 3839.815 -211.8) 
(list 3839.818 -213.4583) 
(list 3839.8209 -215.1167) 
(list 3839.8238 -216.775) 
(list 3839.8267 -218.4333) 
(list 3839.8294 -220.0917) 
(list 3839.8322 -221.75) 
(list 3839.8349 -223.4083) 
(list 3839.8375 -225.0667) 
(list 3839.8401 -226.725) 
(list 3839.8427 -228.3833) 
(list 3839.8452 -230.0417) 
(list 3839.8477 -231.7) 
(list 3839.8501 -233.3583) 
(list 3839.8524 -235.0167) 
(list 3839.8548 -236.675) 
(list 3839.8571 -238.3333) 
(list 3839.8593 -239.9917) 
(list 3839.8615 -241.65) 
(list 3839.8637 -243.3083) 
(list 3839.8658 -244.9667) 
(list 3839.8678 -246.625) 
(list 3839.8699 -248.2833) 
(list 3839.8719 -249.9417) 
(list 3839.8738 -251.6) 
(list 3839.8757 -253.2583) 
(list 3839.8776 -254.9167) 
(list 3839.8794 -256.575) 
(list 3839.8812 -258.2333) 
(list 3839.883 -259.8917) 
(list 3839.8847 -261.55) 
(list 3839.8863 -263.2083) 
(list 3839.888 -264.8667) 
(list 3839.8896 -266.525) 
(list 3839.8911 -268.1833) 
(list 3839.8927 -269.8417) 
(list 3839.8942 -271.5) 
(list 3839.8956 -273.1583) 
(list 3839.8971 -274.8167) 
(list 3839.8984 -276.475) 
(list 3839.8998 -278.1333) 
(list 3839.9011 -279.7917) 
(list 3839.9024 -281.45) 
(list 3839.9037 -283.1083) 
(list 3839.9049 -284.7667) 
(list 3839.9061 -286.425) 
(list 3839.9072 -288.0833) 
(list 3839.9084 -289.7417) 
(list 3839.9095 -291.4) 
(list 3839.9105 -293.0583) 
(list 3839.9116 -294.7167) 
(list 3839.9126 -296.375) 
(list 3839.9136 -298.0333) 
(list 3839.9145 -299.6917) 
(list 3839.9155 -301.35) 
(list 3839.9163 -303.0083) 
(list 3839.9172 -304.6667) 
(list 3839.9181 -306.325) 
(list 3839.9189 -307.9833) 
(list 3839.9197 -309.6417) 
(list 3839.9204 -311.3) 
(list 3839.9212 -312.9583) 
(list 3839.9219 -314.6167) 
(list 3839.9226 -316.275) 
(list 3839.9233 -317.9333) 
(list 3839.9239 -319.5917) 
(list 3839.9245 -321.25) 
(list 3839.9251 -322.9083) 
(list 3839.9257 -324.5667) 
(list 3839.9262 -326.225) 
(list 3839.9268 -327.8833) 
(list 3839.9273 -329.5417) 
(list 3839.9278 -331.2) 
(list 3839.9283 -332.8583) 
(list 3839.9287 -334.5167) 
(list 3839.9291 -336.175) 
(list 3839.9296 -337.8333) 
(list 3839.93 -339.4917) 
(list 3839.9303 -341.15) 
(list 3839.9307 -342.8083) 
(list 3839.931 -344.4667) 
(list 3839.9314 -346.125) 
(list 3839.9317 -347.7833) 
(list 3839.932 -349.4417) 
(list 3839.9322 -351.1) 
(list 3839.9325 -352.7583) 
(list 3839.9328 -354.4167) 
(list 3839.933 -356.075) 
(list 3839.9332 -357.7333) 
(list 3839.9334 -359.3917) 
(list 3839.9336 -361.05) 
(list 3839.9338 -362.7083) 
(list 3839.934 -364.3667) 
(list 3839.9341 -366.025) 
(list 3839.9343 -367.6833) 
(list 3839.9344 -369.3417) 
(list 3839.9345 -371) 
(list 3839.9347 -372.6583) 
(list 3839.9348 -374.3167) 
(list 3839.9349 -375.975) 
(list 3839.9349 -377.6333) 
(list 3839.935 -379.2917) 
(list 3839.9351 -380.95) 
(list 3839.9352 -382.6083) 
(list 3839.9352 -384.2667) 
(list 3839.9353 -385.925) 
(list 3839.9353 -387.5833) 
(list 3839.9353 -389.2417) 
(list 3839.9354 -390.9) 
(list 3839.9354 -392.5583) 
(list 3839.9354 -394.2167) 
(list 3839.9354 -395.875) 
(list 3839.9355 -397.5333) 
(list 3839.9355 -399.1917) 
(list 3839.9355 -400.85) 
(list 3839.9355 -402.5083) 
(list 3839.9355 -404.1667) 
(list 3839.9355 -405.825) 
(list 3839.9355 -407.4833) 
(list 3839.9355 -409.1417) 
(list 3839.9355 -410.8)))
(apply 'command (append '("pline") coords '("c")))
(setq currobj (ssadd (entlast) currobj))
(command "_layer" "set" "prebias" "")
(command "_rectangle" "3839.815,-410.8" "3840.185,-211.8")
(setq currobj (ssadd (entlast) currobj))
(command "_layer" "set" "nitride" "")
(setq singlenanobeam12 currobj)
(setq currobj nil)
(setq currobj (ssadd))
; DRAWING NODE ARRAY
(setq coords (list 
(list 3840.185 -211.8) 
(list 3840.5625 -201.8) 
(list 3840.5625 -201.8) 
(list 3840.5625 -200.8) 
(list 3914.585 -212.6864) 
(list 3914.585 -207.7434) 
(list 3840.5625 -197.357) 
(list 3840.5625 -196.357) 
(list 3840.5625 -196.357) 
(list 3840.2625 -186.357) 
(list 3839.7375 -186.357) 
(list 3839.4375 -196.357) 
(list 3839.4375 -196.357) 
(list 3839.4375 -197.357) 
(list 3765.415 -207.7434) 
(list 3765.415 -212.6864) 
(list 3839.4375 -200.8) 
(list 3839.4375 -201.8) 
(list 3839.4375 -201.8) 
(list 3839.815 -211.8)))
(apply 'command (append '("pline") coords '("c")))
(setq currobj (ssadd (entlast) currobj))
(command "_layer" "set" "prebias" "")
(setq coords (list 
(list 3839.4375 -212.6864) 
(list 3839.4375 -200.8) 
(list 3765.415 -212.6864) 
(list 3765.415 -207.7434) 
(list 3839.4375 -197.357) 
(list 3839.4375 -186.357) 
(list 3840.5625 -186.357) 
(list 3840.5625 -197.357) 
(list 3914.585 -207.7434) 
(list 3914.585 -212.6864) 
(list 3840.5625 -200.8) 
(list 3840.5625 -212.6864)))
(apply 'command (append '("pline") coords '("c")))
(setq currobj (ssadd (entlast) currobj))
(command "_layer" "set" "nitride" "")
(command "_layer" "set" "fda1" "")
(setq coords (list 
(list 3840.5625 -200.657) 
(list 3914.585 -212.5434) 
(list 3914.585 -212.3664) 
(list 3840.5625 -200.58)))
(apply 'command (append '("pline") coords '("c")))
(setq currobj (ssadd (entlast) currobj))
(setq coords (list 
(list 3840.5625 -200.437) 
(list 3914.585 -212.2234) 
(list 3914.585 -212.0464) 
(list 3840.5625 -200.36)))
(apply 'command (append '("pline") coords '("c")))
(setq currobj (ssadd (entlast) currobj))
(setq coords (list 
(list 3840.5625 -200.217) 
(list 3914.585 -211.9034) 
(list 3914.585 -211.7264) 
(list 3840.5625 -200.14)))
(apply 'command (append '("pline") coords '("c")))
(setq currobj (ssadd (entlast) currobj))
(setq coords (list 
(list 3840.5625 -199.997) 
(list 3914.585 -211.5834) 
(list 3914.585 -211.4064) 
(list 3840.5625 -199.92)))
(apply 'command (append '("pline") coords '("c")))
(setq currobj (ssadd (entlast) currobj))
(setq coords (list 
(list 3840.5625 -199.777) 
(list 3914.585 -211.2634) 
(list 3914.585 -211.0864) 
(list 3840.5625 -199.7)))
(apply 'command (append '("pline") coords '("c")))
(setq currobj (ssadd (entlast) currobj))
(setq coords (list 
(list 3840.5625 -199.557) 
(list 3914.585 -210.9434) 
(list 3914.585 -210.7664) 
(list 3840.5625 -199.48)))
(apply 'command (append '("pline") coords '("c")))
(setq currobj (ssadd (entlast) currobj))
(setq coords (list 
(list 3840.5625 -199.337) 
(list 3914.585 -210.6234) 
(list 3914.585 -210.4464) 
(list 3840.5625 -199.26)))
(apply 'command (append '("pline") coords '("c")))
(setq currobj (ssadd (entlast) currobj))
(setq coords (list 
(list 3840.5625 -199.117) 
(list 3914.585 -210.3034) 
(list 3914.585 -210.1264) 
(list 3840.5625 -199.04)))
(apply 'command (append '("pline") coords '("c")))
(setq currobj (ssadd (entlast) currobj))
(setq coords (list 
(list 3840.5625 -198.897) 
(list 3914.585 -209.9834) 
(list 3914.585 -209.8064) 
(list 3840.5625 -198.82)))
(apply 'command (append '("pline") coords '("c")))
(setq currobj (ssadd (entlast) currobj))
(setq coords (list 
(list 3840.5625 -198.677) 
(list 3914.585 -209.6634) 
(list 3914.585 -209.4864) 
(list 3840.5625 -198.6)))
(apply 'command (append '("pline") coords '("c")))
(setq currobj (ssadd (entlast) currobj))
(setq coords (list 
(list 3840.5625 -198.457) 
(list 3914.585 -209.3434) 
(list 3914.585 -209.1664) 
(list 3840.5625 -198.38)))
(apply 'command (append '("pline") coords '("c")))
(setq currobj (ssadd (entlast) currobj))
(setq coords (list 
(list 3840.5625 -198.237) 
(list 3914.585 -209.0234) 
(list 3914.585 -208.8464) 
(list 3840.5625 -198.16)))
(apply 'command (append '("pline") coords '("c")))
(setq currobj (ssadd (entlast) currobj))
(setq coords (list 
(list 3840.5625 -198.017) 
(list 3914.585 -208.7034) 
(list 3914.585 -208.5264) 
(list 3840.5625 -197.94)))
(apply 'command (append '("pline") coords '("c")))
(setq currobj (ssadd (entlast) currobj))
(setq coords (list 
(list 3840.5625 -197.797) 
(list 3914.585 -208.3834) 
(list 3914.585 -208.2064) 
(list 3840.5625 -197.72)))
(apply 'command (append '("pline") coords '("c")))
(setq currobj (ssadd (entlast) currobj))
(setq coords (list 
(list 3840.5625 -197.577) 
(list 3914.585 -208.0634) 
(list 3914.585 -207.8864) 
(list 3840.5625 -197.5)))
(apply 'command (append '("pline") coords '("c")))
(setq currobj (ssadd (entlast) currobj))
(setq coords (list 
(list 3839.4375 -197.5) 
(list 3765.415 -207.8864) 
(list 3765.415 -208.0634) 
(list 3839.4375 -197.577)))
(apply 'command (append '("pline") coords '("c")))
(setq currobj (ssadd (entlast) currobj))
(setq coords (list 
(list 3839.4375 -197.72) 
(list 3765.415 -208.2064) 
(list 3765.415 -208.3834) 
(list 3839.4375 -197.797)))
(apply 'command (append '("pline") coords '("c")))
(setq currobj (ssadd (entlast) currobj))
(setq coords (list 
(list 3839.4375 -197.94) 
(list 3765.415 -208.5264) 
(list 3765.415 -208.7034) 
(list 3839.4375 -198.017)))
(apply 'command (append '("pline") coords '("c")))
(setq currobj (ssadd (entlast) currobj))
(setq coords (list 
(list 3839.4375 -198.16) 
(list 3765.415 -208.8464) 
(list 3765.415 -209.0234) 
(list 3839.4375 -198.237)))
(apply 'command (append '("pline") coords '("c")))
(setq currobj (ssadd (entlast) currobj))
(setq coords (list 
(list 3839.4375 -198.38) 
(list 3765.415 -209.1664) 
(list 3765.415 -209.3434) 
(list 3839.4375 -198.457)))
(apply 'command (append '("pline") coords '("c")))
(setq currobj (ssadd (entlast) currobj))
(setq coords (list 
(list 3839.4375 -198.6) 
(list 3765.415 -209.4864) 
(list 3765.415 -209.6634) 
(list 3839.4375 -198.677)))
(apply 'command (append '("pline") coords '("c")))
(setq currobj (ssadd (entlast) currobj))
(setq coords (list 
(list 3839.4375 -198.82) 
(list 3765.415 -209.8064) 
(list 3765.415 -209.9834) 
(list 3839.4375 -198.897)))
(apply 'command (append '("pline") coords '("c")))
(setq currobj (ssadd (entlast) currobj))
(setq coords (list 
(list 3839.4375 -199.04) 
(list 3765.415 -210.1264) 
(list 3765.415 -210.3034) 
(list 3839.4375 -199.117)))
(apply 'command (append '("pline") coords '("c")))
(setq currobj (ssadd (entlast) currobj))
(setq coords (list 
(list 3839.4375 -199.26) 
(list 3765.415 -210.4464) 
(list 3765.415 -210.6234) 
(list 3839.4375 -199.337)))
(apply 'command (append '("pline") coords '("c")))
(setq currobj (ssadd (entlast) currobj))
(setq coords (list 
(list 3839.4375 -199.48) 
(list 3765.415 -210.7664) 
(list 3765.415 -210.9434) 
(list 3839.4375 -199.557)))
(apply 'command (append '("pline") coords '("c")))
(setq currobj (ssadd (entlast) currobj))
(setq coords (list 
(list 3839.4375 -199.7) 
(list 3765.415 -211.0864) 
(list 3765.415 -211.2634) 
(list 3839.4375 -199.777)))
(apply 'command (append '("pline") coords '("c")))
(setq currobj (ssadd (entlast) currobj))
(setq coords (list 
(list 3839.4375 -199.92) 
(list 3765.415 -211.4064) 
(list 3765.415 -211.5834) 
(list 3839.4375 -199.997)))
(apply 'command (append '("pline") coords '("c")))
(setq currobj (ssadd (entlast) currobj))
(setq coords (list 
(list 3839.4375 -200.14) 
(list 3765.415 -211.7264) 
(list 3765.415 -211.9034) 
(list 3839.4375 -200.217)))
(apply 'command (append '("pline") coords '("c")))
(setq currobj (ssadd (entlast) currobj))
(setq coords (list 
(list 3839.4375 -200.36) 
(list 3765.415 -212.0464) 
(list 3765.415 -212.2234) 
(list 3839.4375 -200.437)))
(apply 'command (append '("pline") coords '("c")))
(setq currobj (ssadd (entlast) currobj))
(setq coords (list 
(list 3839.4375 -200.58) 
(list 3765.415 -212.3664) 
(list 3765.415 -212.5434) 
(list 3839.4375 -200.657)))
(apply 'command (append '("pline") coords '("c")))
(setq currobj (ssadd (entlast) currobj))
(command "_layer" "set" "nitride" "")
(command "_layer" "set" "text" "")
(command "_circle" "3838.985,-211.8" "0.075")
(command "_circle" "3838.985,-211.5" "0.075")
(command "_circle" "3838.985,-211.2" "0.075")
(command "_circle" "3838.985,-210.9" "0.075")
(command "_circle" "3838.985,-210.6" "0.075")
(command "_circle" "3838.685,-211.8" "0.075")
(command "_circle" "3838.685,-211.5" "0.075")
(command "_circle" "3838.685,-211.2" "0.075")
(command "_circle" "3838.685,-210.9" "0.075")
(command "_circle" "3838.685,-210.6" "0.075")
(command "_circle" "3838.385,-211.8" "0.075")
(command "_circle" "3838.385,-211.5" "0.075")
(command "_circle" "3838.385,-211.2" "0.075")
(command "_circle" "3838.385,-210.9" "0.075")
(command "_circle" "3838.385,-210.6" "0.075")
(command "_circle" "3838.085,-211.8" "0.075")
(command "_circle" "3838.085,-211.5" "0.075")
(command "_circle" "3838.085,-211.2" "0.075")
(command "_circle" "3838.085,-210.9" "0.075")
(command "_circle" "3838.085,-210.6" "0.075")
(command "_circle" "3837.785,-211.8" "0.075")
(command "_circle" "3837.785,-211.5" "0.075")
(command "_circle" "3837.785,-211.2" "0.075")
(command "_circle" "3837.785,-210.9" "0.075")
(command "_circle" "3837.785,-210.6" "0.075")
(command "_layer" "set" "nitride" "")
(setq anglednodearray12 currobj)
(setq currobj nil)
(setq currobj (ssadd))
; DRAWING COOLED SINGLE NANOBEAM
(setq coords (list 
(list 3840.2625 -186.357) 
(list 3840.2625 -181.357) 
(list 3839.7375 -181.357) 
(list 3839.7375 -186.357)))
(apply 'command (append '("pline") coords '("c")))
(setq currobj (ssadd (entlast) currobj))
(command "_layer" "set" "prebias" "")
(command "_rectangle" "3839.7375,-186.357" "3840.2625,-181.357")
(setq currobj (ssadd (entlast) currobj))
(command "_layer" "set" "nitride" "")
(setq coords (list 
(list 3840.2625 -181.357) 
(list 3840.5625 -171.357) 
(list 3840.5625 -171.357) 
(list 3840.5625 -170.357) 
(list 3914.585 -171.107) 
(list 3914.585 -166.164) 
(list 3840.5625 -166.914) 
(list 3840.5625 -165.914) 
(list 3840.5625 -165.914) 
(list 3840.2625 -155.914) 
(list 3839.7375 -155.914) 
(list 3839.4375 -165.914) 
(list 3839.4375 -165.914) 
(list 3839.4375 -166.914) 
(list 3765.415 -166.164) 
(list 3765.415 -171.107) 
(list 3839.4375 -170.357) 
(list 3839.4375 -171.357) 
(list 3839.4375 -171.357) 
(list 3839.7375 -181.357)))
(apply 'command (append '("pline") coords '("c")))
(setq currobj (ssadd (entlast) currobj))
(command "_layer" "set" "prebias" "")
(setq coords (list 
(list 3839.4375 -181.357) 
(list 3839.4375 -170.357) 
(list 3765.415 -171.107) 
(list 3765.415 -166.164) 
(list 3839.4375 -166.914) 
(list 3839.4375 -155.914) 
(list 3840.5625 -155.914) 
(list 3840.5625 -166.914) 
(list 3914.585 -166.164) 
(list 3914.585 -171.107) 
(list 3840.5625 -170.357) 
(list 3840.5625 -181.357)))
(apply 'command (append '("pline") coords '("c")))
(setq currobj (ssadd (entlast) currobj))
(command "_layer" "set" "nitride" "")
(command "_layer" "set" "fda1" "")
(setq coords (list 
(list 3840.5625 -170.214) 
(list 3914.585 -170.964) 
(list 3914.585 -170.787) 
(list 3840.5625 -170.137)))
(apply 'command (append '("pline") coords '("c")))
(setq currobj (ssadd (entlast) currobj))
(setq coords (list 
(list 3840.5625 -169.994) 
(list 3914.585 -170.644) 
(list 3914.585 -170.467) 
(list 3840.5625 -169.917)))
(apply 'command (append '("pline") coords '("c")))
(setq currobj (ssadd (entlast) currobj))
(setq coords (list 
(list 3840.5625 -169.774) 
(list 3914.585 -170.324) 
(list 3914.585 -170.147) 
(list 3840.5625 -169.697)))
(apply 'command (append '("pline") coords '("c")))
(setq currobj (ssadd (entlast) currobj))
(setq coords (list 
(list 3840.5625 -169.554) 
(list 3914.585 -170.004) 
(list 3914.585 -169.827) 
(list 3840.5625 -169.477)))
(apply 'command (append '("pline") coords '("c")))
(setq currobj (ssadd (entlast) currobj))
(setq coords (list 
(list 3840.5625 -169.334) 
(list 3914.585 -169.684) 
(list 3914.585 -169.507) 
(list 3840.5625 -169.257)))
(apply 'command (append '("pline") coords '("c")))
(setq currobj (ssadd (entlast) currobj))
(setq coords (list 
(list 3840.5625 -169.114) 
(list 3914.585 -169.364) 
(list 3914.585 -169.187) 
(list 3840.5625 -169.037)))
(apply 'command (append '("pline") coords '("c")))
(setq currobj (ssadd (entlast) currobj))
(setq coords (list 
(list 3840.5625 -168.894) 
(list 3914.585 -169.044) 
(list 3914.585 -168.867) 
(list 3840.5625 -168.817)))
(apply 'command (append '("pline") coords '("c")))
(setq currobj (ssadd (entlast) currobj))
(setq coords (list 
(list 3840.5625 -168.674) 
(list 3914.585 -168.724) 
(list 3914.585 -168.547) 
(list 3840.5625 -168.597)))
(apply 'command (append '("pline") coords '("c")))
(setq currobj (ssadd (entlast) currobj))
(setq coords (list 
(list 3840.5625 -168.454) 
(list 3914.585 -168.404) 
(list 3914.585 -168.227) 
(list 3840.5625 -168.377)))
(apply 'command (append '("pline") coords '("c")))
(setq currobj (ssadd (entlast) currobj))
(setq coords (list 
(list 3840.5625 -168.234) 
(list 3914.585 -168.084) 
(list 3914.585 -167.907) 
(list 3840.5625 -168.157)))
(apply 'command (append '("pline") coords '("c")))
(setq currobj (ssadd (entlast) currobj))
(setq coords (list 
(list 3840.5625 -168.014) 
(list 3914.585 -167.764) 
(list 3914.585 -167.587) 
(list 3840.5625 -167.937)))
(apply 'command (append '("pline") coords '("c")))
(setq currobj (ssadd (entlast) currobj))
(setq coords (list 
(list 3840.5625 -167.794) 
(list 3914.585 -167.444) 
(list 3914.585 -167.267) 
(list 3840.5625 -167.717)))
(apply 'command (append '("pline") coords '("c")))
(setq currobj (ssadd (entlast) currobj))
(setq coords (list 
(list 3840.5625 -167.574) 
(list 3914.585 -167.124) 
(list 3914.585 -166.947) 
(list 3840.5625 -167.497)))
(apply 'command (append '("pline") coords '("c")))
(setq currobj (ssadd (entlast) currobj))
(setq coords (list 
(list 3840.5625 -167.354) 
(list 3914.585 -166.804) 
(list 3914.585 -166.627) 
(list 3840.5625 -167.277)))
(apply 'command (append '("pline") coords '("c")))
(setq currobj (ssadd (entlast) currobj))
(setq coords (list 
(list 3840.5625 -167.134) 
(list 3914.585 -166.484) 
(list 3914.585 -166.307) 
(list 3840.5625 -167.057)))
(apply 'command (append '("pline") coords '("c")))
(setq currobj (ssadd (entlast) currobj))
(setq coords (list 
(list 3839.4375 -167.057) 
(list 3765.415 -166.307) 
(list 3765.415 -166.484) 
(list 3839.4375 -167.134)))
(apply 'command (append '("pline") coords '("c")))
(setq currobj (ssadd (entlast) currobj))
(setq coords (list 
(list 3839.4375 -167.277) 
(list 3765.415 -166.627) 
(list 3765.415 -166.804) 
(list 3839.4375 -167.354)))
(apply 'command (append '("pline") coords '("c")))
(setq currobj (ssadd (entlast) currobj))
(setq coords (list 
(list 3839.4375 -167.497) 
(list 3765.415 -166.947) 
(list 3765.415 -167.124) 
(list 3839.4375 -167.574)))
(apply 'command (append '("pline") coords '("c")))
(setq currobj (ssadd (entlast) currobj))
(setq coords (list 
(list 3839.4375 -167.717) 
(list 3765.415 -167.267) 
(list 3765.415 -167.444) 
(list 3839.4375 -167.794)))
(apply 'command (append '("pline") coords '("c")))
(setq currobj (ssadd (entlast) currobj))
(setq coords (list 
(list 3839.4375 -167.937) 
(list 3765.415 -167.587) 
(list 3765.415 -167.764) 
(list 3839.4375 -168.014)))
(apply 'command (append '("pline") coords '("c")))
(setq currobj (ssadd (entlast) currobj))
(setq coords (list 
(list 3839.4375 -168.157) 
(list 3765.415 -167.907) 
(list 3765.415 -168.084) 
(list 3839.4375 -168.234)))
(apply 'command (append '("pline") coords '("c")))
(setq currobj (ssadd (entlast) currobj))
(setq coords (list 
(list 3839.4375 -168.377) 
(list 3765.415 -168.227) 
(list 3765.415 -168.404) 
(list 3839.4375 -168.454)))
(apply 'command (append '("pline") coords '("c")))
(setq currobj (ssadd (entlast) currobj))
(setq coords (list 
(list 3839.4375 -168.597) 
(list 3765.415 -168.547) 
(list 3765.415 -168.724) 
(list 3839.4375 -168.674)))
(apply 'command (append '("pline") coords '("c")))
(setq currobj (ssadd (entlast) currobj))
(setq coords (list 
(list 3839.4375 -168.817) 
(list 3765.415 -168.867) 
(list 3765.415 -169.044) 
(list 3839.4375 -168.894)))
(apply 'command (append '("pline") coords '("c")))
(setq currobj (ssadd (entlast) currobj))
(setq coords (list 
(list 3839.4375 -169.037) 
(list 3765.415 -169.187) 
(list 3765.415 -169.364) 
(list 3839.4375 -169.114)))
(apply 'command (append '("pline") coords '("c")))
(setq currobj (ssadd (entlast) currobj))
(setq coords (list 
(list 3839.4375 -169.257) 
(list 3765.415 -169.507) 
(list 3765.415 -169.684) 
(list 3839.4375 -169.334)))
(apply 'command (append '("pline") coords '("c")))
(setq currobj (ssadd (entlast) currobj))
(setq coords (list 
(list 3839.4375 -169.477) 
(list 3765.415 -169.827) 
(list 3765.415 -170.004) 
(list 3839.4375 -169.554)))
(apply 'command (append '("pline") coords '("c")))
(setq currobj (ssadd (entlast) currobj))
(setq coords (list 
(list 3839.4375 -169.697) 
(list 3765.415 -170.147) 
(list 3765.415 -170.324) 
(list 3839.4375 -169.774)))
(apply 'command (append '("pline") coords '("c")))
(setq currobj (ssadd (entlast) currobj))
(setq coords (list 
(list 3839.4375 -169.917) 
(list 3765.415 -170.467) 
(list 3765.415 -170.644) 
(list 3839.4375 -169.994)))
(apply 'command (append '("pline") coords '("c")))
(setq currobj (ssadd (entlast) currobj))
(setq coords (list 
(list 3839.4375 -170.137) 
(list 3765.415 -170.787) 
(list 3765.415 -170.964) 
(list 3839.4375 -170.214)))
(apply 'command (append '("pline") coords '("c")))
(setq currobj (ssadd (entlast) currobj))
(command "_layer" "set" "nitride" "")
(command "_layer" "set" "text" "")
(command "_circle" "3839.0625,-181.357" "0.075")
(command "_circle" "3839.0625,-181.057" "0.075")
(command "_circle" "3839.0625,-180.757" "0.075")
(command "_circle" "3839.0625,-180.457" "0.075")
(command "_circle" "3839.0625,-180.157" "0.075")
(command "_circle" "3838.7625,-181.357" "0.075")
(command "_circle" "3838.7625,-181.057" "0.075")
(command "_circle" "3838.7625,-180.757" "0.075")
(command "_circle" "3838.7625,-180.457" "0.075")
(command "_circle" "3838.7625,-180.157" "0.075")
(command "_circle" "3838.4625,-181.357" "0.075")
(command "_circle" "3838.4625,-181.057" "0.075")
(command "_circle" "3838.4625,-180.757" "0.075")
(command "_circle" "3838.4625,-180.457" "0.075")
(command "_circle" "3838.4625,-180.157" "0.075")
(command "_circle" "3838.1625,-181.357" "0.075")
(command "_circle" "3838.1625,-181.057" "0.075")
(command "_circle" "3838.1625,-180.757" "0.075")
(command "_circle" "3838.1625,-180.457" "0.075")
(command "_circle" "3838.1625,-180.157" "0.075")
(command "_circle" "3837.8625,-181.357" "0.075")
(command "_circle" "3837.8625,-181.057" "0.075")
(command "_circle" "3837.8625,-180.757" "0.075")
(command "_circle" "3837.8625,-180.457" "0.075")
(command "_circle" "3837.8625,-180.157" "0.075")
(command "_layer" "set" "nitride" "")
(setq coords (list 
(list 3840.2625 -155.914) 
(list 3840.2625 -40.2693) 
(list 3839.7375 -40.2693) 
(list 3839.7375 -155.914)))
(apply 'command (append '("pline") coords '("c")))
(setq currobj (ssadd (entlast) currobj))
(command "_layer" "set" "prebias" "")
(command "_rectangle" "3839.7375,-155.914" "3840.2625,-40.2693")
(setq currobj (ssadd (entlast) currobj))
(command "_layer" "set" "nitride" "")
(setq coords (list 
(list 3840.2625 -40.2693) 
(list 3840.5625 -30.2693) 
(list 3840.5625 -30.2693) 
(list 3840.5625 -29.2693) 
(list 3914.585 -30.0193) 
(list 3914.585 -25.0763) 
(list 3840.5625 -25.8263) 
(list 3840.5625 -24.8263) 
(list 3840.5625 -24.8263) 
(list 3840.2625 -14.8263) 
(list 3839.7375 -14.8263) 
(list 3839.4375 -24.8263) 
(list 3839.4375 -24.8263) 
(list 3839.4375 -25.8263) 
(list 3765.415 -25.0763) 
(list 3765.415 -30.0193) 
(list 3839.4375 -29.2693) 
(list 3839.4375 -30.2693) 
(list 3839.4375 -30.2693) 
(list 3839.7375 -40.2693)))
(apply 'command (append '("pline") coords '("c")))
(setq currobj (ssadd (entlast) currobj))
(command "_layer" "set" "prebias" "")
(setq coords (list 
(list 3839.4375 -40.2693) 
(list 3839.4375 -29.2693) 
(list 3765.415 -30.0193) 
(list 3765.415 -25.0763) 
(list 3839.4375 -25.8263) 
(list 3839.4375 -14.8263) 
(list 3840.5625 -14.8263) 
(list 3840.5625 -25.8263) 
(list 3914.585 -25.0763) 
(list 3914.585 -30.0193) 
(list 3840.5625 -29.2693) 
(list 3840.5625 -40.2693)))
(apply 'command (append '("pline") coords '("c")))
(setq currobj (ssadd (entlast) currobj))
(command "_layer" "set" "nitride" "")
(command "_layer" "set" "fda1" "")
(setq coords (list 
(list 3840.5625 -29.1263) 
(list 3914.585 -29.8763) 
(list 3914.585 -29.6993) 
(list 3840.5625 -29.0493)))
(apply 'command (append '("pline") coords '("c")))
(setq currobj (ssadd (entlast) currobj))
(setq coords (list 
(list 3840.5625 -28.9063) 
(list 3914.585 -29.5563) 
(list 3914.585 -29.3793) 
(list 3840.5625 -28.8293)))
(apply 'command (append '("pline") coords '("c")))
(setq currobj (ssadd (entlast) currobj))
(setq coords (list 
(list 3840.5625 -28.6863) 
(list 3914.585 -29.2363) 
(list 3914.585 -29.0593) 
(list 3840.5625 -28.6093)))
(apply 'command (append '("pline") coords '("c")))
(setq currobj (ssadd (entlast) currobj))
(setq coords (list 
(list 3840.5625 -28.4663) 
(list 3914.585 -28.9163) 
(list 3914.585 -28.7393) 
(list 3840.5625 -28.3893)))
(apply 'command (append '("pline") coords '("c")))
(setq currobj (ssadd (entlast) currobj))
(setq coords (list 
(list 3840.5625 -28.2463) 
(list 3914.585 -28.5963) 
(list 3914.585 -28.4193) 
(list 3840.5625 -28.1693)))
(apply 'command (append '("pline") coords '("c")))
(setq currobj (ssadd (entlast) currobj))
(setq coords (list 
(list 3840.5625 -28.0263) 
(list 3914.585 -28.2763) 
(list 3914.585 -28.0993) 
(list 3840.5625 -27.9493)))
(apply 'command (append '("pline") coords '("c")))
(setq currobj (ssadd (entlast) currobj))
(setq coords (list 
(list 3840.5625 -27.8063) 
(list 3914.585 -27.9563) 
(list 3914.585 -27.7793) 
(list 3840.5625 -27.7293)))
(apply 'command (append '("pline") coords '("c")))
(setq currobj (ssadd (entlast) currobj))
(setq coords (list 
(list 3840.5625 -27.5863) 
(list 3914.585 -27.6363) 
(list 3914.585 -27.4593) 
(list 3840.5625 -27.5093)))
(apply 'command (append '("pline") coords '("c")))
(setq currobj (ssadd (entlast) currobj))
(setq coords (list 
(list 3840.5625 -27.3663) 
(list 3914.585 -27.3163) 
(list 3914.585 -27.1393) 
(list 3840.5625 -27.2893)))
(apply 'command (append '("pline") coords '("c")))
(setq currobj (ssadd (entlast) currobj))
(setq coords (list 
(list 3840.5625 -27.1463) 
(list 3914.585 -26.9963) 
(list 3914.585 -26.8193) 
(list 3840.5625 -27.0693)))
(apply 'command (append '("pline") coords '("c")))
(setq currobj (ssadd (entlast) currobj))
(setq coords (list 
(list 3840.5625 -26.9263) 
(list 3914.585 -26.6763) 
(list 3914.585 -26.4993) 
(list 3840.5625 -26.8493)))
(apply 'command (append '("pline") coords '("c")))
(setq currobj (ssadd (entlast) currobj))
(setq coords (list 
(list 3840.5625 -26.7063) 
(list 3914.585 -26.3563) 
(list 3914.585 -26.1793) 
(list 3840.5625 -26.6293)))
(apply 'command (append '("pline") coords '("c")))
(setq currobj (ssadd (entlast) currobj))
(setq coords (list 
(list 3840.5625 -26.4863) 
(list 3914.585 -26.0363) 
(list 3914.585 -25.8593) 
(list 3840.5625 -26.4093)))
(apply 'command (append '("pline") coords '("c")))
(setq currobj (ssadd (entlast) currobj))
(setq coords (list 
(list 3840.5625 -26.2663) 
(list 3914.585 -25.7163) 
(list 3914.585 -25.5393) 
(list 3840.5625 -26.1893)))
(apply 'command (append '("pline") coords '("c")))
(setq currobj (ssadd (entlast) currobj))
(setq coords (list 
(list 3840.5625 -26.0463) 
(list 3914.585 -25.3963) 
(list 3914.585 -25.2193) 
(list 3840.5625 -25.9693)))
(apply 'command (append '("pline") coords '("c")))
(setq currobj (ssadd (entlast) currobj))
(setq coords (list 
(list 3839.4375 -25.9693) 
(list 3765.415 -25.2193) 
(list 3765.415 -25.3963) 
(list 3839.4375 -26.0463)))
(apply 'command (append '("pline") coords '("c")))
(setq currobj (ssadd (entlast) currobj))
(setq coords (list 
(list 3839.4375 -26.1893) 
(list 3765.415 -25.5393) 
(list 3765.415 -25.7163) 
(list 3839.4375 -26.2663)))
(apply 'command (append '("pline") coords '("c")))
(setq currobj (ssadd (entlast) currobj))
(setq coords (list 
(list 3839.4375 -26.4093) 
(list 3765.415 -25.8593) 
(list 3765.415 -26.0363) 
(list 3839.4375 -26.4863)))
(apply 'command (append '("pline") coords '("c")))
(setq currobj (ssadd (entlast) currobj))
(setq coords (list 
(list 3839.4375 -26.6293) 
(list 3765.415 -26.1793) 
(list 3765.415 -26.3563) 
(list 3839.4375 -26.7063)))
(apply 'command (append '("pline") coords '("c")))
(setq currobj (ssadd (entlast) currobj))
(setq coords (list 
(list 3839.4375 -26.8493) 
(list 3765.415 -26.4993) 
(list 3765.415 -26.6763) 
(list 3839.4375 -26.9263)))
(apply 'command (append '("pline") coords '("c")))
(setq currobj (ssadd (entlast) currobj))
(setq coords (list 
(list 3839.4375 -27.0693) 
(list 3765.415 -26.8193) 
(list 3765.415 -26.9963) 
(list 3839.4375 -27.1463)))
(apply 'command (append '("pline") coords '("c")))
(setq currobj (ssadd (entlast) currobj))
(setq coords (list 
(list 3839.4375 -27.2893) 
(list 3765.415 -27.1393) 
(list 3765.415 -27.3163) 
(list 3839.4375 -27.3663)))
(apply 'command (append '("pline") coords '("c")))
(setq currobj (ssadd (entlast) currobj))
(setq coords (list 
(list 3839.4375 -27.5093) 
(list 3765.415 -27.4593) 
(list 3765.415 -27.6363) 
(list 3839.4375 -27.5863)))
(apply 'command (append '("pline") coords '("c")))
(setq currobj (ssadd (entlast) currobj))
(setq coords (list 
(list 3839.4375 -27.7293) 
(list 3765.415 -27.7793) 
(list 3765.415 -27.9563) 
(list 3839.4375 -27.8063)))
(apply 'command (append '("pline") coords '("c")))
(setq currobj (ssadd (entlast) currobj))
(setq coords (list 
(list 3839.4375 -27.9493) 
(list 3765.415 -28.0993) 
(list 3765.415 -28.2763) 
(list 3839.4375 -28.0263)))
(apply 'command (append '("pline") coords '("c")))
(setq currobj (ssadd (entlast) currobj))
(setq coords (list 
(list 3839.4375 -28.1693) 
(list 3765.415 -28.4193) 
(list 3765.415 -28.5963) 
(list 3839.4375 -28.2463)))
(apply 'command (append '("pline") coords '("c")))
(setq currobj (ssadd (entlast) currobj))
(setq coords (list 
(list 3839.4375 -28.3893) 
(list 3765.415 -28.7393) 
(list 3765.415 -28.9163) 
(list 3839.4375 -28.4663)))
(apply 'command (append '("pline") coords '("c")))
(setq currobj (ssadd (entlast) currobj))
(setq coords (list 
(list 3839.4375 -28.6093) 
(list 3765.415 -29.0593) 
(list 3765.415 -29.2363) 
(list 3839.4375 -28.6863)))
(apply 'command (append '("pline") coords '("c")))
(setq currobj (ssadd (entlast) currobj))
(setq coords (list 
(list 3839.4375 -28.8293) 
(list 3765.415 -29.3793) 
(list 3765.415 -29.5563) 
(list 3839.4375 -28.9063)))
(apply 'command (append '("pline") coords '("c")))
(setq currobj (ssadd (entlast) currobj))
(setq coords (list 
(list 3839.4375 -29.0493) 
(list 3765.415 -29.6993) 
(list 3765.415 -29.8763) 
(list 3839.4375 -29.1263)))
(apply 'command (append '("pline") coords '("c")))
(setq currobj (ssadd (entlast) currobj))
(command "_layer" "set" "nitride" "")
(command "_layer" "set" "text" "")
(command "_circle" "3839.0625,-40.2693" "0.075")
(command "_circle" "3839.0625,-39.9693" "0.075")
(command "_circle" "3839.0625,-39.6693" "0.075")
(command "_circle" "3839.0625,-39.3693" "0.075")
(command "_circle" "3839.0625,-39.0693" "0.075")
(command "_circle" "3838.7625,-40.2693" "0.075")
(command "_circle" "3838.7625,-39.9693" "0.075")
(command "_circle" "3838.7625,-39.6693" "0.075")
(command "_circle" "3838.7625,-39.3693" "0.075")
(command "_circle" "3838.7625,-39.0693" "0.075")
(command "_circle" "3838.4625,-40.2693" "0.075")
(command "_circle" "3838.4625,-39.9693" "0.075")
(command "_circle" "3838.4625,-39.6693" "0.075")
(command "_circle" "3838.4625,-39.3693" "0.075")
(command "_circle" "3838.4625,-39.0693" "0.075")
(command "_circle" "3838.1625,-40.2693" "0.075")
(command "_circle" "3838.1625,-39.9693" "0.075")
(command "_circle" "3838.1625,-39.6693" "0.075")
(command "_circle" "3838.1625,-39.3693" "0.075")
(command "_circle" "3838.1625,-39.0693" "0.075")
(command "_circle" "3837.8625,-40.2693" "0.075")
(command "_circle" "3837.8625,-39.9693" "0.075")
(command "_circle" "3837.8625,-39.6693" "0.075")
(command "_circle" "3837.8625,-39.3693" "0.075")
(command "_circle" "3837.8625,-39.0693" "0.075")
(command "_layer" "set" "nitride" "")
(setq coords (list 
(list 3840.2625 -14.8263) 
(list 3840.2625 100.8184) 
(list 3839.7375 100.8184) 
(list 3839.7375 -14.8263)))
(apply 'command (append '("pline") coords '("c")))
(setq currobj (ssadd (entlast) currobj))
(command "_layer" "set" "prebias" "")
(command "_rectangle" "3839.7375,-14.8263" "3840.2625,100.8184")
(setq currobj (ssadd (entlast) currobj))
(command "_layer" "set" "nitride" "")
(setq coords (list 
(list 3840.2625 100.8184) 
(list 3840.5625 110.8184) 
(list 3840.5625 110.8184) 
(list 3840.5625 111.8184) 
(list 3914.585 111.0684) 
(list 3914.585 116.0114) 
(list 3840.5625 115.2614) 
(list 3840.5625 116.2614) 
(list 3840.5625 116.2614) 
(list 3840.2625 126.2614) 
(list 3839.7375 126.2614) 
(list 3839.4375 116.2614) 
(list 3839.4375 116.2614) 
(list 3839.4375 115.2614) 
(list 3765.415 116.0114) 
(list 3765.415 111.0684) 
(list 3839.4375 111.8184) 
(list 3839.4375 110.8184) 
(list 3839.4375 110.8184) 
(list 3839.7375 100.8184)))
(apply 'command (append '("pline") coords '("c")))
(setq currobj (ssadd (entlast) currobj))
(command "_layer" "set" "prebias" "")
(setq coords (list 
(list 3839.4375 100.8184) 
(list 3839.4375 111.8184) 
(list 3765.415 111.0684) 
(list 3765.415 116.0114) 
(list 3839.4375 115.2614) 
(list 3839.4375 126.2614) 
(list 3840.5625 126.2614) 
(list 3840.5625 115.2614) 
(list 3914.585 116.0114) 
(list 3914.585 111.0684) 
(list 3840.5625 111.8184) 
(list 3840.5625 100.8184)))
(apply 'command (append '("pline") coords '("c")))
(setq currobj (ssadd (entlast) currobj))
(command "_layer" "set" "nitride" "")
(command "_layer" "set" "fda1" "")
(setq coords (list 
(list 3840.5625 111.9614) 
(list 3914.585 111.2114) 
(list 3914.585 111.3884) 
(list 3840.5625 112.0384)))
(apply 'command (append '("pline") coords '("c")))
(setq currobj (ssadd (entlast) currobj))
(setq coords (list 
(list 3840.5625 112.1814) 
(list 3914.585 111.5314) 
(list 3914.585 111.7084) 
(list 3840.5625 112.2584)))
(apply 'command (append '("pline") coords '("c")))
(setq currobj (ssadd (entlast) currobj))
(setq coords (list 
(list 3840.5625 112.4014) 
(list 3914.585 111.8514) 
(list 3914.585 112.0284) 
(list 3840.5625 112.4784)))
(apply 'command (append '("pline") coords '("c")))
(setq currobj (ssadd (entlast) currobj))
(setq coords (list 
(list 3840.5625 112.6214) 
(list 3914.585 112.1714) 
(list 3914.585 112.3484) 
(list 3840.5625 112.6984)))
(apply 'command (append '("pline") coords '("c")))
(setq currobj (ssadd (entlast) currobj))
(setq coords (list 
(list 3840.5625 112.8414) 
(list 3914.585 112.4914) 
(list 3914.585 112.6684) 
(list 3840.5625 112.9184)))
(apply 'command (append '("pline") coords '("c")))
(setq currobj (ssadd (entlast) currobj))
(setq coords (list 
(list 3840.5625 113.0614) 
(list 3914.585 112.8114) 
(list 3914.585 112.9884) 
(list 3840.5625 113.1384)))
(apply 'command (append '("pline") coords '("c")))
(setq currobj (ssadd (entlast) currobj))
(setq coords (list 
(list 3840.5625 113.2814) 
(list 3914.585 113.1314) 
(list 3914.585 113.3084) 
(list 3840.5625 113.3584)))
(apply 'command (append '("pline") coords '("c")))
(setq currobj (ssadd (entlast) currobj))
(setq coords (list 
(list 3840.5625 113.5014) 
(list 3914.585 113.4514) 
(list 3914.585 113.6284) 
(list 3840.5625 113.5784)))
(apply 'command (append '("pline") coords '("c")))
(setq currobj (ssadd (entlast) currobj))
(setq coords (list 
(list 3840.5625 113.7214) 
(list 3914.585 113.7714) 
(list 3914.585 113.9484) 
(list 3840.5625 113.7984)))
(apply 'command (append '("pline") coords '("c")))
(setq currobj (ssadd (entlast) currobj))
(setq coords (list 
(list 3840.5625 113.9414) 
(list 3914.585 114.0914) 
(list 3914.585 114.2684) 
(list 3840.5625 114.0184)))
(apply 'command (append '("pline") coords '("c")))
(setq currobj (ssadd (entlast) currobj))
(setq coords (list 
(list 3840.5625 114.1614) 
(list 3914.585 114.4114) 
(list 3914.585 114.5884) 
(list 3840.5625 114.2384)))
(apply 'command (append '("pline") coords '("c")))
(setq currobj (ssadd (entlast) currobj))
(setq coords (list 
(list 3840.5625 114.3814) 
(list 3914.585 114.7314) 
(list 3914.585 114.9084) 
(list 3840.5625 114.4584)))
(apply 'command (append '("pline") coords '("c")))
(setq currobj (ssadd (entlast) currobj))
(setq coords (list 
(list 3840.5625 114.6014) 
(list 3914.585 115.0514) 
(list 3914.585 115.2284) 
(list 3840.5625 114.6784)))
(apply 'command (append '("pline") coords '("c")))
(setq currobj (ssadd (entlast) currobj))
(setq coords (list 
(list 3840.5625 114.8214) 
(list 3914.585 115.3714) 
(list 3914.585 115.5484) 
(list 3840.5625 114.8984)))
(apply 'command (append '("pline") coords '("c")))
(setq currobj (ssadd (entlast) currobj))
(setq coords (list 
(list 3840.5625 115.0414) 
(list 3914.585 115.6914) 
(list 3914.585 115.8684) 
(list 3840.5625 115.1184)))
(apply 'command (append '("pline") coords '("c")))
(setq currobj (ssadd (entlast) currobj))
(setq coords (list 
(list 3839.4375 115.1184) 
(list 3765.415 115.8684) 
(list 3765.415 115.6914) 
(list 3839.4375 115.0414)))
(apply 'command (append '("pline") coords '("c")))
(setq currobj (ssadd (entlast) currobj))
(setq coords (list 
(list 3839.4375 114.8984) 
(list 3765.415 115.5484) 
(list 3765.415 115.3714) 
(list 3839.4375 114.8214)))
(apply 'command (append '("pline") coords '("c")))
(setq currobj (ssadd (entlast) currobj))
(setq coords (list 
(list 3839.4375 114.6784) 
(list 3765.415 115.2284) 
(list 3765.415 115.0514) 
(list 3839.4375 114.6014)))
(apply 'command (append '("pline") coords '("c")))
(setq currobj (ssadd (entlast) currobj))
(setq coords (list 
(list 3839.4375 114.4584) 
(list 3765.415 114.9084) 
(list 3765.415 114.7314) 
(list 3839.4375 114.3814)))
(apply 'command (append '("pline") coords '("c")))
(setq currobj (ssadd (entlast) currobj))
(setq coords (list 
(list 3839.4375 114.2384) 
(list 3765.415 114.5884) 
(list 3765.415 114.4114) 
(list 3839.4375 114.1614)))
(apply 'command (append '("pline") coords '("c")))
(setq currobj (ssadd (entlast) currobj))
(setq coords (list 
(list 3839.4375 114.0184) 
(list 3765.415 114.2684) 
(list 3765.415 114.0914) 
(list 3839.4375 113.9414)))
(apply 'command (append '("pline") coords '("c")))
(setq currobj (ssadd (entlast) currobj))
(setq coords (list 
(list 3839.4375 113.7984) 
(list 3765.415 113.9484) 
(list 3765.415 113.7714) 
(list 3839.4375 113.7214)))
(apply 'command (append '("pline") coords '("c")))
(setq currobj (ssadd (entlast) currobj))
(setq coords (list 
(list 3839.4375 113.5784) 
(list 3765.415 113.6284) 
(list 3765.415 113.4514) 
(list 3839.4375 113.5014)))
(apply 'command (append '("pline") coords '("c")))
(setq currobj (ssadd (entlast) currobj))
(setq coords (list 
(list 3839.4375 113.3584) 
(list 3765.415 113.3084) 
(list 3765.415 113.1314) 
(list 3839.4375 113.2814)))
(apply 'command (append '("pline") coords '("c")))
(setq currobj (ssadd (entlast) currobj))
(setq coords (list 
(list 3839.4375 113.1384) 
(list 3765.415 112.9884) 
(list 3765.415 112.8114) 
(list 3839.4375 113.0614)))
(apply 'command (append '("pline") coords '("c")))
(setq currobj (ssadd (entlast) currobj))
(setq coords (list 
(list 3839.4375 112.9184) 
(list 3765.415 112.6684) 
(list 3765.415 112.4914) 
(list 3839.4375 112.8414)))
(apply 'command (append '("pline") coords '("c")))
(setq currobj (ssadd (entlast) currobj))
(setq coords (list 
(list 3839.4375 112.6984) 
(list 3765.415 112.3484) 
(list 3765.415 112.1714) 
(list 3839.4375 112.6214)))
(apply 'command (append '("pline") coords '("c")))
(setq currobj (ssadd (entlast) currobj))
(setq coords (list 
(list 3839.4375 112.4784) 
(list 3765.415 112.0284) 
(list 3765.415 111.8514) 
(list 3839.4375 112.4014)))
(apply 'command (append '("pline") coords '("c")))
(setq currobj (ssadd (entlast) currobj))
(setq coords (list 
(list 3839.4375 112.2584) 
(list 3765.415 111.7084) 
(list 3765.415 111.5314) 
(list 3839.4375 112.1814)))
(apply 'command (append '("pline") coords '("c")))
(setq currobj (ssadd (entlast) currobj))
(setq coords (list 
(list 3839.4375 112.0384) 
(list 3765.415 111.3884) 
(list 3765.415 111.2114) 
(list 3839.4375 111.9614)))
(apply 'command (append '("pline") coords '("c")))
(setq currobj (ssadd (entlast) currobj))
(command "_layer" "set" "nitride" "")
(command "_layer" "set" "text" "")
(command "_circle" "3839.0625,100.8184" "0.075")
(command "_circle" "3839.0625,101.1184" "0.075")
(command "_circle" "3839.0625,101.4184" "0.075")
(command "_circle" "3839.0625,101.7184" "0.075")
(command "_circle" "3839.0625,102.0184" "0.075")
(command "_circle" "3838.7625,100.8184" "0.075")
(command "_circle" "3838.7625,101.1184" "0.075")
(command "_circle" "3838.7625,101.4184" "0.075")
(command "_circle" "3838.7625,101.7184" "0.075")
(command "_circle" "3838.7625,102.0184" "0.075")
(command "_circle" "3838.4625,100.8184" "0.075")
(command "_circle" "3838.4625,101.1184" "0.075")
(command "_circle" "3838.4625,101.4184" "0.075")
(command "_circle" "3838.4625,101.7184" "0.075")
(command "_circle" "3838.4625,102.0184" "0.075")
(command "_circle" "3838.1625,100.8184" "0.075")
(command "_circle" "3838.1625,101.1184" "0.075")
(command "_circle" "3838.1625,101.4184" "0.075")
(command "_circle" "3838.1625,101.7184" "0.075")
(command "_circle" "3838.1625,102.0184" "0.075")
(command "_circle" "3837.8625,100.8184" "0.075")
(command "_circle" "3837.8625,101.1184" "0.075")
(command "_circle" "3837.8625,101.4184" "0.075")
(command "_circle" "3837.8625,101.7184" "0.075")
(command "_circle" "3837.8625,102.0184" "0.075")
(command "_layer" "set" "nitride" "")
(setq coords (list 
(list 3840.2625 126.2614) 
(list 3840.2625 241.9061) 
(list 3839.7375 241.9061) 
(list 3839.7375 126.2614)))
(apply 'command (append '("pline") coords '("c")))
(setq currobj (ssadd (entlast) currobj))
(command "_layer" "set" "prebias" "")
(command "_rectangle" "3839.7375,126.2614" "3840.2625,241.9061")
(setq currobj (ssadd (entlast) currobj))
(command "_layer" "set" "nitride" "")
(setq coords (list 
(list 3840.2625 241.9061) 
(list 3840.5625 251.9061) 
(list 3840.5625 251.9061) 
(list 3840.5625 252.9061) 
(list 3914.585 252.1561) 
(list 3914.585 257.0991) 
(list 3840.5625 256.3491) 
(list 3840.5625 257.3491) 
(list 3840.5625 257.3491) 
(list 3840.2625 267.3491) 
(list 3839.7375 267.3491) 
(list 3839.4375 257.3491) 
(list 3839.4375 257.3491) 
(list 3839.4375 256.3491) 
(list 3765.415 257.0991) 
(list 3765.415 252.1561) 
(list 3839.4375 252.9061) 
(list 3839.4375 251.9061) 
(list 3839.4375 251.9061) 
(list 3839.7375 241.9061)))
(apply 'command (append '("pline") coords '("c")))
(setq currobj (ssadd (entlast) currobj))
(command "_layer" "set" "prebias" "")
(setq coords (list 
(list 3839.4375 241.9061) 
(list 3839.4375 252.9061) 
(list 3765.415 252.1561) 
(list 3765.415 257.0991) 
(list 3839.4375 256.3491) 
(list 3839.4375 267.3491) 
(list 3840.5625 267.3491) 
(list 3840.5625 256.3491) 
(list 3914.585 257.0991) 
(list 3914.585 252.1561) 
(list 3840.5625 252.9061) 
(list 3840.5625 241.9061)))
(apply 'command (append '("pline") coords '("c")))
(setq currobj (ssadd (entlast) currobj))
(command "_layer" "set" "nitride" "")
(command "_layer" "set" "fda1" "")
(setq coords (list 
(list 3840.5625 253.0491) 
(list 3914.585 252.2991) 
(list 3914.585 252.4761) 
(list 3840.5625 253.1261)))
(apply 'command (append '("pline") coords '("c")))
(setq currobj (ssadd (entlast) currobj))
(setq coords (list 
(list 3840.5625 253.2691) 
(list 3914.585 252.6191) 
(list 3914.585 252.7961) 
(list 3840.5625 253.3461)))
(apply 'command (append '("pline") coords '("c")))
(setq currobj (ssadd (entlast) currobj))
(setq coords (list 
(list 3840.5625 253.4891) 
(list 3914.585 252.9391) 
(list 3914.585 253.1161) 
(list 3840.5625 253.5661)))
(apply 'command (append '("pline") coords '("c")))
(setq currobj (ssadd (entlast) currobj))
(setq coords (list 
(list 3840.5625 253.7091) 
(list 3914.585 253.2591) 
(list 3914.585 253.4361) 
(list 3840.5625 253.7861)))
(apply 'command (append '("pline") coords '("c")))
(setq currobj (ssadd (entlast) currobj))
(setq coords (list 
(list 3840.5625 253.9291) 
(list 3914.585 253.5791) 
(list 3914.585 253.7561) 
(list 3840.5625 254.0061)))
(apply 'command (append '("pline") coords '("c")))
(setq currobj (ssadd (entlast) currobj))
(setq coords (list 
(list 3840.5625 254.1491) 
(list 3914.585 253.8991) 
(list 3914.585 254.0761) 
(list 3840.5625 254.2261)))
(apply 'command (append '("pline") coords '("c")))
(setq currobj (ssadd (entlast) currobj))
(setq coords (list 
(list 3840.5625 254.3691) 
(list 3914.585 254.2191) 
(list 3914.585 254.3961) 
(list 3840.5625 254.4461)))
(apply 'command (append '("pline") coords '("c")))
(setq currobj (ssadd (entlast) currobj))
(setq coords (list 
(list 3840.5625 254.5891) 
(list 3914.585 254.5391) 
(list 3914.585 254.7161) 
(list 3840.5625 254.6661)))
(apply 'command (append '("pline") coords '("c")))
(setq currobj (ssadd (entlast) currobj))
(setq coords (list 
(list 3840.5625 254.8091) 
(list 3914.585 254.8591) 
(list 3914.585 255.0361) 
(list 3840.5625 254.8861)))
(apply 'command (append '("pline") coords '("c")))
(setq currobj (ssadd (entlast) currobj))
(setq coords (list 
(list 3840.5625 255.0291) 
(list 3914.585 255.1791) 
(list 3914.585 255.3561) 
(list 3840.5625 255.1061)))
(apply 'command (append '("pline") coords '("c")))
(setq currobj (ssadd (entlast) currobj))
(setq coords (list 
(list 3840.5625 255.2491) 
(list 3914.585 255.4991) 
(list 3914.585 255.6761) 
(list 3840.5625 255.3261)))
(apply 'command (append '("pline") coords '("c")))
(setq currobj (ssadd (entlast) currobj))
(setq coords (list 
(list 3840.5625 255.4691) 
(list 3914.585 255.8191) 
(list 3914.585 255.9961) 
(list 3840.5625 255.5461)))
(apply 'command (append '("pline") coords '("c")))
(setq currobj (ssadd (entlast) currobj))
(setq coords (list 
(list 3840.5625 255.6891) 
(list 3914.585 256.1391) 
(list 3914.585 256.3161) 
(list 3840.5625 255.7661)))
(apply 'command (append '("pline") coords '("c")))
(setq currobj (ssadd (entlast) currobj))
(setq coords (list 
(list 3840.5625 255.9091) 
(list 3914.585 256.4591) 
(list 3914.585 256.6361) 
(list 3840.5625 255.9861)))
(apply 'command (append '("pline") coords '("c")))
(setq currobj (ssadd (entlast) currobj))
(setq coords (list 
(list 3840.5625 256.1291) 
(list 3914.585 256.7791) 
(list 3914.585 256.9561) 
(list 3840.5625 256.2061)))
(apply 'command (append '("pline") coords '("c")))
(setq currobj (ssadd (entlast) currobj))
(setq coords (list 
(list 3839.4375 256.2061) 
(list 3765.415 256.9561) 
(list 3765.415 256.7791) 
(list 3839.4375 256.1291)))
(apply 'command (append '("pline") coords '("c")))
(setq currobj (ssadd (entlast) currobj))
(setq coords (list 
(list 3839.4375 255.9861) 
(list 3765.415 256.6361) 
(list 3765.415 256.4591) 
(list 3839.4375 255.9091)))
(apply 'command (append '("pline") coords '("c")))
(setq currobj (ssadd (entlast) currobj))
(setq coords (list 
(list 3839.4375 255.7661) 
(list 3765.415 256.3161) 
(list 3765.415 256.1391) 
(list 3839.4375 255.6891)))
(apply 'command (append '("pline") coords '("c")))
(setq currobj (ssadd (entlast) currobj))
(setq coords (list 
(list 3839.4375 255.5461) 
(list 3765.415 255.9961) 
(list 3765.415 255.8191) 
(list 3839.4375 255.4691)))
(apply 'command (append '("pline") coords '("c")))
(setq currobj (ssadd (entlast) currobj))
(setq coords (list 
(list 3839.4375 255.3261) 
(list 3765.415 255.6761) 
(list 3765.415 255.4991) 
(list 3839.4375 255.2491)))
(apply 'command (append '("pline") coords '("c")))
(setq currobj (ssadd (entlast) currobj))
(setq coords (list 
(list 3839.4375 255.1061) 
(list 3765.415 255.3561) 
(list 3765.415 255.1791) 
(list 3839.4375 255.0291)))
(apply 'command (append '("pline") coords '("c")))
(setq currobj (ssadd (entlast) currobj))
(setq coords (list 
(list 3839.4375 254.8861) 
(list 3765.415 255.0361) 
(list 3765.415 254.8591) 
(list 3839.4375 254.8091)))
(apply 'command (append '("pline") coords '("c")))
(setq currobj (ssadd (entlast) currobj))
(setq coords (list 
(list 3839.4375 254.6661) 
(list 3765.415 254.7161) 
(list 3765.415 254.5391) 
(list 3839.4375 254.5891)))
(apply 'command (append '("pline") coords '("c")))
(setq currobj (ssadd (entlast) currobj))
(setq coords (list 
(list 3839.4375 254.4461) 
(list 3765.415 254.3961) 
(list 3765.415 254.2191) 
(list 3839.4375 254.3691)))
(apply 'command (append '("pline") coords '("c")))
(setq currobj (ssadd (entlast) currobj))
(setq coords (list 
(list 3839.4375 254.2261) 
(list 3765.415 254.0761) 
(list 3765.415 253.8991) 
(list 3839.4375 254.1491)))
(apply 'command (append '("pline") coords '("c")))
(setq currobj (ssadd (entlast) currobj))
(setq coords (list 
(list 3839.4375 254.0061) 
(list 3765.415 253.7561) 
(list 3765.415 253.5791) 
(list 3839.4375 253.9291)))
(apply 'command (append '("pline") coords '("c")))
(setq currobj (ssadd (entlast) currobj))
(setq coords (list 
(list 3839.4375 253.7861) 
(list 3765.415 253.4361) 
(list 3765.415 253.2591) 
(list 3839.4375 253.7091)))
(apply 'command (append '("pline") coords '("c")))
(setq currobj (ssadd (entlast) currobj))
(setq coords (list 
(list 3839.4375 253.5661) 
(list 3765.415 253.1161) 
(list 3765.415 252.9391) 
(list 3839.4375 253.4891)))
(apply 'command (append '("pline") coords '("c")))
(setq currobj (ssadd (entlast) currobj))
(setq coords (list 
(list 3839.4375 253.3461) 
(list 3765.415 252.7961) 
(list 3765.415 252.6191) 
(list 3839.4375 253.2691)))
(apply 'command (append '("pline") coords '("c")))
(setq currobj (ssadd (entlast) currobj))
(setq coords (list 
(list 3839.4375 253.1261) 
(list 3765.415 252.4761) 
(list 3765.415 252.2991) 
(list 3839.4375 253.0491)))
(apply 'command (append '("pline") coords '("c")))
(setq currobj (ssadd (entlast) currobj))
(command "_layer" "set" "nitride" "")
(command "_layer" "set" "text" "")
(command "_circle" "3839.0625,241.9061" "0.075")
(command "_circle" "3839.0625,242.2061" "0.075")
(command "_circle" "3839.0625,242.5061" "0.075")
(command "_circle" "3839.0625,242.8061" "0.075")
(command "_circle" "3839.0625,243.1061" "0.075")
(command "_circle" "3838.7625,241.9061" "0.075")
(command "_circle" "3838.7625,242.2061" "0.075")
(command "_circle" "3838.7625,242.5061" "0.075")
(command "_circle" "3838.7625,242.8061" "0.075")
(command "_circle" "3838.7625,243.1061" "0.075")
(command "_circle" "3838.4625,241.9061" "0.075")
(command "_circle" "3838.4625,242.2061" "0.075")
(command "_circle" "3838.4625,242.5061" "0.075")
(command "_circle" "3838.4625,242.8061" "0.075")
(command "_circle" "3838.4625,243.1061" "0.075")
(command "_circle" "3838.1625,241.9061" "0.075")
(command "_circle" "3838.1625,242.2061" "0.075")
(command "_circle" "3838.1625,242.5061" "0.075")
(command "_circle" "3838.1625,242.8061" "0.075")
(command "_circle" "3838.1625,243.1061" "0.075")
(command "_circle" "3837.8625,241.9061" "0.075")
(command "_circle" "3837.8625,242.2061" "0.075")
(command "_circle" "3837.8625,242.5061" "0.075")
(command "_circle" "3837.8625,242.8061" "0.075")
(command "_circle" "3837.8625,243.1061" "0.075")
(command "_layer" "set" "nitride" "")
(setq coords (list 
(list 3840.2625 267.3491) 
(list 3840.2625 382.9939) 
(list 3839.7375 382.9939) 
(list 3839.7375 267.3491)))
(apply 'command (append '("pline") coords '("c")))
(setq currobj (ssadd (entlast) currobj))
(command "_layer" "set" "prebias" "")
(command "_rectangle" "3839.7375,267.3491" "3840.2625,382.9939")
(setq currobj (ssadd (entlast) currobj))
(command "_layer" "set" "nitride" "")
(setq coords (list 
(list 3840.2625 382.9939) 
(list 3840.5625 392.9939) 
(list 3840.5625 392.9939) 
(list 3840.5625 393.9939) 
(list 3914.585 393.2439) 
(list 3914.585 398.1869) 
(list 3840.5625 397.4369) 
(list 3840.5625 398.4369) 
(list 3840.5625 398.4369) 
(list 3840.2625 408.4369) 
(list 3839.7375 408.4369) 
(list 3839.4375 398.4369) 
(list 3839.4375 398.4369) 
(list 3839.4375 397.4369) 
(list 3765.415 398.1869) 
(list 3765.415 393.2439) 
(list 3839.4375 393.9939) 
(list 3839.4375 392.9939) 
(list 3839.4375 392.9939) 
(list 3839.7375 382.9939)))
(apply 'command (append '("pline") coords '("c")))
(setq currobj (ssadd (entlast) currobj))
(command "_layer" "set" "prebias" "")
(setq coords (list 
(list 3839.4375 382.9939) 
(list 3839.4375 393.9939) 
(list 3765.415 393.2439) 
(list 3765.415 398.1869) 
(list 3839.4375 397.4369) 
(list 3839.4375 408.4369) 
(list 3840.5625 408.4369) 
(list 3840.5625 397.4369) 
(list 3914.585 398.1869) 
(list 3914.585 393.2439) 
(list 3840.5625 393.9939) 
(list 3840.5625 382.9939)))
(apply 'command (append '("pline") coords '("c")))
(setq currobj (ssadd (entlast) currobj))
(command "_layer" "set" "nitride" "")
(command "_layer" "set" "fda1" "")
(setq coords (list 
(list 3840.5625 394.1369) 
(list 3914.585 393.3869) 
(list 3914.585 393.5639) 
(list 3840.5625 394.2139)))
(apply 'command (append '("pline") coords '("c")))
(setq currobj (ssadd (entlast) currobj))
(setq coords (list 
(list 3840.5625 394.3569) 
(list 3914.585 393.7069) 
(list 3914.585 393.8839) 
(list 3840.5625 394.4339)))
(apply 'command (append '("pline") coords '("c")))
(setq currobj (ssadd (entlast) currobj))
(setq coords (list 
(list 3840.5625 394.5769) 
(list 3914.585 394.0269) 
(list 3914.585 394.2039) 
(list 3840.5625 394.6539)))
(apply 'command (append '("pline") coords '("c")))
(setq currobj (ssadd (entlast) currobj))
(setq coords (list 
(list 3840.5625 394.7969) 
(list 3914.585 394.3469) 
(list 3914.585 394.5239) 
(list 3840.5625 394.8739)))
(apply 'command (append '("pline") coords '("c")))
(setq currobj (ssadd (entlast) currobj))
(setq coords (list 
(list 3840.5625 395.0169) 
(list 3914.585 394.6669) 
(list 3914.585 394.8439) 
(list 3840.5625 395.0939)))
(apply 'command (append '("pline") coords '("c")))
(setq currobj (ssadd (entlast) currobj))
(setq coords (list 
(list 3840.5625 395.2369) 
(list 3914.585 394.9869) 
(list 3914.585 395.1639) 
(list 3840.5625 395.3139)))
(apply 'command (append '("pline") coords '("c")))
(setq currobj (ssadd (entlast) currobj))
(setq coords (list 
(list 3840.5625 395.4569) 
(list 3914.585 395.3069) 
(list 3914.585 395.4839) 
(list 3840.5625 395.5339)))
(apply 'command (append '("pline") coords '("c")))
(setq currobj (ssadd (entlast) currobj))
(setq coords (list 
(list 3840.5625 395.6769) 
(list 3914.585 395.6269) 
(list 3914.585 395.8039) 
(list 3840.5625 395.7539)))
(apply 'command (append '("pline") coords '("c")))
(setq currobj (ssadd (entlast) currobj))
(setq coords (list 
(list 3840.5625 395.8969) 
(list 3914.585 395.9469) 
(list 3914.585 396.1239) 
(list 3840.5625 395.9739)))
(apply 'command (append '("pline") coords '("c")))
(setq currobj (ssadd (entlast) currobj))
(setq coords (list 
(list 3840.5625 396.1169) 
(list 3914.585 396.2669) 
(list 3914.585 396.4439) 
(list 3840.5625 396.1939)))
(apply 'command (append '("pline") coords '("c")))
(setq currobj (ssadd (entlast) currobj))
(setq coords (list 
(list 3840.5625 396.3369) 
(list 3914.585 396.5869) 
(list 3914.585 396.7639) 
(list 3840.5625 396.4139)))
(apply 'command (append '("pline") coords '("c")))
(setq currobj (ssadd (entlast) currobj))
(setq coords (list 
(list 3840.5625 396.5569) 
(list 3914.585 396.9069) 
(list 3914.585 397.0839) 
(list 3840.5625 396.6339)))
(apply 'command (append '("pline") coords '("c")))
(setq currobj (ssadd (entlast) currobj))
(setq coords (list 
(list 3840.5625 396.7769) 
(list 3914.585 397.2269) 
(list 3914.585 397.4039) 
(list 3840.5625 396.8539)))
(apply 'command (append '("pline") coords '("c")))
(setq currobj (ssadd (entlast) currobj))
(setq coords (list 
(list 3840.5625 396.9969) 
(list 3914.585 397.5469) 
(list 3914.585 397.7239) 
(list 3840.5625 397.0739)))
(apply 'command (append '("pline") coords '("c")))
(setq currobj (ssadd (entlast) currobj))
(setq coords (list 
(list 3840.5625 397.2169) 
(list 3914.585 397.8669) 
(list 3914.585 398.0439) 
(list 3840.5625 397.2939)))
(apply 'command (append '("pline") coords '("c")))
(setq currobj (ssadd (entlast) currobj))
(setq coords (list 
(list 3839.4375 397.2939) 
(list 3765.415 398.0439) 
(list 3765.415 397.8669) 
(list 3839.4375 397.2169)))
(apply 'command (append '("pline") coords '("c")))
(setq currobj (ssadd (entlast) currobj))
(setq coords (list 
(list 3839.4375 397.0739) 
(list 3765.415 397.7239) 
(list 3765.415 397.5469) 
(list 3839.4375 396.9969)))
(apply 'command (append '("pline") coords '("c")))
(setq currobj (ssadd (entlast) currobj))
(setq coords (list 
(list 3839.4375 396.8539) 
(list 3765.415 397.4039) 
(list 3765.415 397.2269) 
(list 3839.4375 396.7769)))
(apply 'command (append '("pline") coords '("c")))
(setq currobj (ssadd (entlast) currobj))
(setq coords (list 
(list 3839.4375 396.6339) 
(list 3765.415 397.0839) 
(list 3765.415 396.9069) 
(list 3839.4375 396.5569)))
(apply 'command (append '("pline") coords '("c")))
(setq currobj (ssadd (entlast) currobj))
(setq coords (list 
(list 3839.4375 396.4139) 
(list 3765.415 396.7639) 
(list 3765.415 396.5869) 
(list 3839.4375 396.3369)))
(apply 'command (append '("pline") coords '("c")))
(setq currobj (ssadd (entlast) currobj))
(setq coords (list 
(list 3839.4375 396.1939) 
(list 3765.415 396.4439) 
(list 3765.415 396.2669) 
(list 3839.4375 396.1169)))
(apply 'command (append '("pline") coords '("c")))
(setq currobj (ssadd (entlast) currobj))
(setq coords (list 
(list 3839.4375 395.9739) 
(list 3765.415 396.1239) 
(list 3765.415 395.9469) 
(list 3839.4375 395.8969)))
(apply 'command (append '("pline") coords '("c")))
(setq currobj (ssadd (entlast) currobj))
(setq coords (list 
(list 3839.4375 395.7539) 
(list 3765.415 395.8039) 
(list 3765.415 395.6269) 
(list 3839.4375 395.6769)))
(apply 'command (append '("pline") coords '("c")))
(setq currobj (ssadd (entlast) currobj))
(setq coords (list 
(list 3839.4375 395.5339) 
(list 3765.415 395.4839) 
(list 3765.415 395.3069) 
(list 3839.4375 395.4569)))
(apply 'command (append '("pline") coords '("c")))
(setq currobj (ssadd (entlast) currobj))
(setq coords (list 
(list 3839.4375 395.3139) 
(list 3765.415 395.1639) 
(list 3765.415 394.9869) 
(list 3839.4375 395.2369)))
(apply 'command (append '("pline") coords '("c")))
(setq currobj (ssadd (entlast) currobj))
(setq coords (list 
(list 3839.4375 395.0939) 
(list 3765.415 394.8439) 
(list 3765.415 394.6669) 
(list 3839.4375 395.0169)))
(apply 'command (append '("pline") coords '("c")))
(setq currobj (ssadd (entlast) currobj))
(setq coords (list 
(list 3839.4375 394.8739) 
(list 3765.415 394.5239) 
(list 3765.415 394.3469) 
(list 3839.4375 394.7969)))
(apply 'command (append '("pline") coords '("c")))
(setq currobj (ssadd (entlast) currobj))
(setq coords (list 
(list 3839.4375 394.6539) 
(list 3765.415 394.2039) 
(list 3765.415 394.0269) 
(list 3839.4375 394.5769)))
(apply 'command (append '("pline") coords '("c")))
(setq currobj (ssadd (entlast) currobj))
(setq coords (list 
(list 3839.4375 394.4339) 
(list 3765.415 393.8839) 
(list 3765.415 393.7069) 
(list 3839.4375 394.3569)))
(apply 'command (append '("pline") coords '("c")))
(setq currobj (ssadd (entlast) currobj))
(setq coords (list 
(list 3839.4375 394.2139) 
(list 3765.415 393.5639) 
(list 3765.415 393.3869) 
(list 3839.4375 394.1369)))
(apply 'command (append '("pline") coords '("c")))
(setq currobj (ssadd (entlast) currobj))
(command "_layer" "set" "nitride" "")
(command "_layer" "set" "text" "")
(command "_circle" "3839.0625,382.9939" "0.075")
(command "_circle" "3839.0625,383.2939" "0.075")
(command "_circle" "3839.0625,383.5939" "0.075")
(command "_circle" "3839.0625,383.8939" "0.075")
(command "_circle" "3839.0625,384.1939" "0.075")
(command "_circle" "3838.7625,382.9939" "0.075")
(command "_circle" "3838.7625,383.2939" "0.075")
(command "_circle" "3838.7625,383.5939" "0.075")
(command "_circle" "3838.7625,383.8939" "0.075")
(command "_circle" "3838.7625,384.1939" "0.075")
(command "_circle" "3838.4625,382.9939" "0.075")
(command "_circle" "3838.4625,383.2939" "0.075")
(command "_circle" "3838.4625,383.5939" "0.075")
(command "_circle" "3838.4625,383.8939" "0.075")
(command "_circle" "3838.4625,384.1939" "0.075")
(command "_circle" "3838.1625,382.9939" "0.075")
(command "_circle" "3838.1625,383.2939" "0.075")
(command "_circle" "3838.1625,383.5939" "0.075")
(command "_circle" "3838.1625,383.8939" "0.075")
(command "_circle" "3838.1625,384.1939" "0.075")
(command "_circle" "3837.8625,382.9939" "0.075")
(command "_circle" "3837.8625,383.2939" "0.075")
(command "_circle" "3837.8625,383.5939" "0.075")
(command "_circle" "3837.8625,383.8939" "0.075")
(command "_circle" "3837.8625,384.1939" "0.075")
(command "_layer" "set" "nitride" "")
(setq coords (list 
(list 3840.2625 408.4369) 
(list 3840.2625 524.0816) 
(list 3839.7375 524.0816) 
(list 3839.7375 408.4369)))
(apply 'command (append '("pline") coords '("c")))
(setq currobj (ssadd (entlast) currobj))
(command "_layer" "set" "prebias" "")
(command "_rectangle" "3839.7375,408.4369" "3840.2625,524.0816")
(setq currobj (ssadd (entlast) currobj))
(command "_layer" "set" "nitride" "")
(setq coords (list 
(list 3840.2625 524.0816) 
(list 3840.5625 534.0816) 
(list 3840.5625 534.0816) 
(list 3840.5625 535.0816) 
(list 3914.585 534.3316) 
(list 3914.585 539.2746) 
(list 3840.5625 538.5246) 
(list 3840.5625 539.5246) 
(list 3840.5625 539.5246) 
(list 3840.2625 549.5246) 
(list 3839.7375 549.5246) 
(list 3839.4375 539.5246) 
(list 3839.4375 539.5246) 
(list 3839.4375 538.5246) 
(list 3765.415 539.2746) 
(list 3765.415 534.3316) 
(list 3839.4375 535.0816) 
(list 3839.4375 534.0816) 
(list 3839.4375 534.0816) 
(list 3839.7375 524.0816)))
(apply 'command (append '("pline") coords '("c")))
(setq currobj (ssadd (entlast) currobj))
(command "_layer" "set" "prebias" "")
(setq coords (list 
(list 3839.4375 524.0816) 
(list 3839.4375 535.0816) 
(list 3765.415 534.3316) 
(list 3765.415 539.2746) 
(list 3839.4375 538.5246) 
(list 3839.4375 549.5246) 
(list 3840.5625 549.5246) 
(list 3840.5625 538.5246) 
(list 3914.585 539.2746) 
(list 3914.585 534.3316) 
(list 3840.5625 535.0816) 
(list 3840.5625 524.0816)))
(apply 'command (append '("pline") coords '("c")))
(setq currobj (ssadd (entlast) currobj))
(command "_layer" "set" "nitride" "")
(command "_layer" "set" "fda1" "")
(setq coords (list 
(list 3840.5625 535.2246) 
(list 3914.585 534.4746) 
(list 3914.585 534.6516) 
(list 3840.5625 535.3016)))
(apply 'command (append '("pline") coords '("c")))
(setq currobj (ssadd (entlast) currobj))
(setq coords (list 
(list 3840.5625 535.4446) 
(list 3914.585 534.7946) 
(list 3914.585 534.9716) 
(list 3840.5625 535.5216)))
(apply 'command (append '("pline") coords '("c")))
(setq currobj (ssadd (entlast) currobj))
(setq coords (list 
(list 3840.5625 535.6646) 
(list 3914.585 535.1146) 
(list 3914.585 535.2916) 
(list 3840.5625 535.7416)))
(apply 'command (append '("pline") coords '("c")))
(setq currobj (ssadd (entlast) currobj))
(setq coords (list 
(list 3840.5625 535.8846) 
(list 3914.585 535.4346) 
(list 3914.585 535.6116) 
(list 3840.5625 535.9616)))
(apply 'command (append '("pline") coords '("c")))
(setq currobj (ssadd (entlast) currobj))
(setq coords (list 
(list 3840.5625 536.1046) 
(list 3914.585 535.7546) 
(list 3914.585 535.9316) 
(list 3840.5625 536.1816)))
(apply 'command (append '("pline") coords '("c")))
(setq currobj (ssadd (entlast) currobj))
(setq coords (list 
(list 3840.5625 536.3246) 
(list 3914.585 536.0746) 
(list 3914.585 536.2516) 
(list 3840.5625 536.4016)))
(apply 'command (append '("pline") coords '("c")))
(setq currobj (ssadd (entlast) currobj))
(setq coords (list 
(list 3840.5625 536.5446) 
(list 3914.585 536.3946) 
(list 3914.585 536.5716) 
(list 3840.5625 536.6216)))
(apply 'command (append '("pline") coords '("c")))
(setq currobj (ssadd (entlast) currobj))
(setq coords (list 
(list 3840.5625 536.7646) 
(list 3914.585 536.7146) 
(list 3914.585 536.8916) 
(list 3840.5625 536.8416)))
(apply 'command (append '("pline") coords '("c")))
(setq currobj (ssadd (entlast) currobj))
(setq coords (list 
(list 3840.5625 536.9846) 
(list 3914.585 537.0346) 
(list 3914.585 537.2116) 
(list 3840.5625 537.0616)))
(apply 'command (append '("pline") coords '("c")))
(setq currobj (ssadd (entlast) currobj))
(setq coords (list 
(list 3840.5625 537.2046) 
(list 3914.585 537.3546) 
(list 3914.585 537.5316) 
(list 3840.5625 537.2816)))
(apply 'command (append '("pline") coords '("c")))
(setq currobj (ssadd (entlast) currobj))
(setq coords (list 
(list 3840.5625 537.4246) 
(list 3914.585 537.6746) 
(list 3914.585 537.8516) 
(list 3840.5625 537.5016)))
(apply 'command (append '("pline") coords '("c")))
(setq currobj (ssadd (entlast) currobj))
(setq coords (list 
(list 3840.5625 537.6446) 
(list 3914.585 537.9946) 
(list 3914.585 538.1716) 
(list 3840.5625 537.7216)))
(apply 'command (append '("pline") coords '("c")))
(setq currobj (ssadd (entlast) currobj))
(setq coords (list 
(list 3840.5625 537.8646) 
(list 3914.585 538.3146) 
(list 3914.585 538.4916) 
(list 3840.5625 537.9416)))
(apply 'command (append '("pline") coords '("c")))
(setq currobj (ssadd (entlast) currobj))
(setq coords (list 
(list 3840.5625 538.0846) 
(list 3914.585 538.6346) 
(list 3914.585 538.8116) 
(list 3840.5625 538.1616)))
(apply 'command (append '("pline") coords '("c")))
(setq currobj (ssadd (entlast) currobj))
(setq coords (list 
(list 3840.5625 538.3046) 
(list 3914.585 538.9546) 
(list 3914.585 539.1316) 
(list 3840.5625 538.3816)))
(apply 'command (append '("pline") coords '("c")))
(setq currobj (ssadd (entlast) currobj))
(setq coords (list 
(list 3839.4375 538.3816) 
(list 3765.415 539.1316) 
(list 3765.415 538.9546) 
(list 3839.4375 538.3046)))
(apply 'command (append '("pline") coords '("c")))
(setq currobj (ssadd (entlast) currobj))
(setq coords (list 
(list 3839.4375 538.1616) 
(list 3765.415 538.8116) 
(list 3765.415 538.6346) 
(list 3839.4375 538.0846)))
(apply 'command (append '("pline") coords '("c")))
(setq currobj (ssadd (entlast) currobj))
(setq coords (list 
(list 3839.4375 537.9416) 
(list 3765.415 538.4916) 
(list 3765.415 538.3146) 
(list 3839.4375 537.8646)))
(apply 'command (append '("pline") coords '("c")))
(setq currobj (ssadd (entlast) currobj))
(setq coords (list 
(list 3839.4375 537.7216) 
(list 3765.415 538.1716) 
(list 3765.415 537.9946) 
(list 3839.4375 537.6446)))
(apply 'command (append '("pline") coords '("c")))
(setq currobj (ssadd (entlast) currobj))
(setq coords (list 
(list 3839.4375 537.5016) 
(list 3765.415 537.8516) 
(list 3765.415 537.6746) 
(list 3839.4375 537.4246)))
(apply 'command (append '("pline") coords '("c")))
(setq currobj (ssadd (entlast) currobj))
(setq coords (list 
(list 3839.4375 537.2816) 
(list 3765.415 537.5316) 
(list 3765.415 537.3546) 
(list 3839.4375 537.2046)))
(apply 'command (append '("pline") coords '("c")))
(setq currobj (ssadd (entlast) currobj))
(setq coords (list 
(list 3839.4375 537.0616) 
(list 3765.415 537.2116) 
(list 3765.415 537.0346) 
(list 3839.4375 536.9846)))
(apply 'command (append '("pline") coords '("c")))
(setq currobj (ssadd (entlast) currobj))
(setq coords (list 
(list 3839.4375 536.8416) 
(list 3765.415 536.8916) 
(list 3765.415 536.7146) 
(list 3839.4375 536.7646)))
(apply 'command (append '("pline") coords '("c")))
(setq currobj (ssadd (entlast) currobj))
(setq coords (list 
(list 3839.4375 536.6216) 
(list 3765.415 536.5716) 
(list 3765.415 536.3946) 
(list 3839.4375 536.5446)))
(apply 'command (append '("pline") coords '("c")))
(setq currobj (ssadd (entlast) currobj))
(setq coords (list 
(list 3839.4375 536.4016) 
(list 3765.415 536.2516) 
(list 3765.415 536.0746) 
(list 3839.4375 536.3246)))
(apply 'command (append '("pline") coords '("c")))
(setq currobj (ssadd (entlast) currobj))
(setq coords (list 
(list 3839.4375 536.1816) 
(list 3765.415 535.9316) 
(list 3765.415 535.7546) 
(list 3839.4375 536.1046)))
(apply 'command (append '("pline") coords '("c")))
(setq currobj (ssadd (entlast) currobj))
(setq coords (list 
(list 3839.4375 535.9616) 
(list 3765.415 535.6116) 
(list 3765.415 535.4346) 
(list 3839.4375 535.8846)))
(apply 'command (append '("pline") coords '("c")))
(setq currobj (ssadd (entlast) currobj))
(setq coords (list 
(list 3839.4375 535.7416) 
(list 3765.415 535.2916) 
(list 3765.415 535.1146) 
(list 3839.4375 535.6646)))
(apply 'command (append '("pline") coords '("c")))
(setq currobj (ssadd (entlast) currobj))
(setq coords (list 
(list 3839.4375 535.5216) 
(list 3765.415 534.9716) 
(list 3765.415 534.7946) 
(list 3839.4375 535.4446)))
(apply 'command (append '("pline") coords '("c")))
(setq currobj (ssadd (entlast) currobj))
(setq coords (list 
(list 3839.4375 535.3016) 
(list 3765.415 534.6516) 
(list 3765.415 534.4746) 
(list 3839.4375 535.2246)))
(apply 'command (append '("pline") coords '("c")))
(setq currobj (ssadd (entlast) currobj))
(command "_layer" "set" "nitride" "")
(command "_layer" "set" "text" "")
(command "_circle" "3839.0625,524.0816" "0.075")
(command "_circle" "3839.0625,524.3816" "0.075")
(command "_circle" "3839.0625,524.6816" "0.075")
(command "_circle" "3839.0625,524.9816" "0.075")
(command "_circle" "3839.0625,525.2816" "0.075")
(command "_circle" "3838.7625,524.0816" "0.075")
(command "_circle" "3838.7625,524.3816" "0.075")
(command "_circle" "3838.7625,524.6816" "0.075")
(command "_circle" "3838.7625,524.9816" "0.075")
(command "_circle" "3838.7625,525.2816" "0.075")
(command "_circle" "3838.4625,524.0816" "0.075")
(command "_circle" "3838.4625,524.3816" "0.075")
(command "_circle" "3838.4625,524.6816" "0.075")
(command "_circle" "3838.4625,524.9816" "0.075")
(command "_circle" "3838.4625,525.2816" "0.075")
(command "_circle" "3838.1625,524.0816" "0.075")
(command "_circle" "3838.1625,524.3816" "0.075")
(command "_circle" "3838.1625,524.6816" "0.075")
(command "_circle" "3838.1625,524.9816" "0.075")
(command "_circle" "3838.1625,525.2816" "0.075")
(command "_circle" "3837.8625,524.0816" "0.075")
(command "_circle" "3837.8625,524.3816" "0.075")
(command "_circle" "3837.8625,524.6816" "0.075")
(command "_circle" "3837.8625,524.9816" "0.075")
(command "_circle" "3837.8625,525.2816" "0.075")
(command "_layer" "set" "nitride" "")
(setq coords (list 
(list 3840.2625 549.5246) 
(list 3840.2625 665.1693) 
(list 3839.7375 665.1693) 
(list 3839.7375 549.5246)))
(apply 'command (append '("pline") coords '("c")))
(setq currobj (ssadd (entlast) currobj))
(command "_layer" "set" "prebias" "")
(command "_rectangle" "3839.7375,549.5246" "3840.2625,665.1693")
(setq currobj (ssadd (entlast) currobj))
(command "_layer" "set" "nitride" "")
(setq coords (list 
(list 3840.2625 665.1693) 
(list 3840.5625 675.1693) 
(list 3840.5625 675.1693) 
(list 3840.5625 676.1693) 
(list 3914.585 675.4193) 
(list 3914.585 680.3623) 
(list 3840.5625 679.6123) 
(list 3840.5625 680.6123) 
(list 3840.5625 680.6123) 
(list 3840.2625 690.6123) 
(list 3839.7375 690.6123) 
(list 3839.4375 680.6123) 
(list 3839.4375 680.6123) 
(list 3839.4375 679.6123) 
(list 3765.415 680.3623) 
(list 3765.415 675.4193) 
(list 3839.4375 676.1693) 
(list 3839.4375 675.1693) 
(list 3839.4375 675.1693) 
(list 3839.7375 665.1693)))
(apply 'command (append '("pline") coords '("c")))
(setq currobj (ssadd (entlast) currobj))
(command "_layer" "set" "prebias" "")
(setq coords (list 
(list 3839.4375 665.1693) 
(list 3839.4375 676.1693) 
(list 3765.415 675.4193) 
(list 3765.415 680.3623) 
(list 3839.4375 679.6123) 
(list 3839.4375 690.6123) 
(list 3840.5625 690.6123) 
(list 3840.5625 679.6123) 
(list 3914.585 680.3623) 
(list 3914.585 675.4193) 
(list 3840.5625 676.1693) 
(list 3840.5625 665.1693)))
(apply 'command (append '("pline") coords '("c")))
(setq currobj (ssadd (entlast) currobj))
(command "_layer" "set" "nitride" "")
(command "_layer" "set" "fda1" "")
(setq coords (list 
(list 3840.5625 676.3123) 
(list 3914.585 675.5623) 
(list 3914.585 675.7393) 
(list 3840.5625 676.3893)))
(apply 'command (append '("pline") coords '("c")))
(setq currobj (ssadd (entlast) currobj))
(setq coords (list 
(list 3840.5625 676.5323) 
(list 3914.585 675.8823) 
(list 3914.585 676.0593) 
(list 3840.5625 676.6093)))
(apply 'command (append '("pline") coords '("c")))
(setq currobj (ssadd (entlast) currobj))
(setq coords (list 
(list 3840.5625 676.7523) 
(list 3914.585 676.2023) 
(list 3914.585 676.3793) 
(list 3840.5625 676.8293)))
(apply 'command (append '("pline") coords '("c")))
(setq currobj (ssadd (entlast) currobj))
(setq coords (list 
(list 3840.5625 676.9723) 
(list 3914.585 676.5223) 
(list 3914.585 676.6993) 
(list 3840.5625 677.0493)))
(apply 'command (append '("pline") coords '("c")))
(setq currobj (ssadd (entlast) currobj))
(setq coords (list 
(list 3840.5625 677.1923) 
(list 3914.585 676.8423) 
(list 3914.585 677.0193) 
(list 3840.5625 677.2693)))
(apply 'command (append '("pline") coords '("c")))
(setq currobj (ssadd (entlast) currobj))
(setq coords (list 
(list 3840.5625 677.4123) 
(list 3914.585 677.1623) 
(list 3914.585 677.3393) 
(list 3840.5625 677.4893)))
(apply 'command (append '("pline") coords '("c")))
(setq currobj (ssadd (entlast) currobj))
(setq coords (list 
(list 3840.5625 677.6323) 
(list 3914.585 677.4823) 
(list 3914.585 677.6593) 
(list 3840.5625 677.7093)))
(apply 'command (append '("pline") coords '("c")))
(setq currobj (ssadd (entlast) currobj))
(setq coords (list 
(list 3840.5625 677.8523) 
(list 3914.585 677.8023) 
(list 3914.585 677.9793) 
(list 3840.5625 677.9293)))
(apply 'command (append '("pline") coords '("c")))
(setq currobj (ssadd (entlast) currobj))
(setq coords (list 
(list 3840.5625 678.0723) 
(list 3914.585 678.1223) 
(list 3914.585 678.2993) 
(list 3840.5625 678.1493)))
(apply 'command (append '("pline") coords '("c")))
(setq currobj (ssadd (entlast) currobj))
(setq coords (list 
(list 3840.5625 678.2923) 
(list 3914.585 678.4423) 
(list 3914.585 678.6193) 
(list 3840.5625 678.3693)))
(apply 'command (append '("pline") coords '("c")))
(setq currobj (ssadd (entlast) currobj))
(setq coords (list 
(list 3840.5625 678.5123) 
(list 3914.585 678.7623) 
(list 3914.585 678.9393) 
(list 3840.5625 678.5893)))
(apply 'command (append '("pline") coords '("c")))
(setq currobj (ssadd (entlast) currobj))
(setq coords (list 
(list 3840.5625 678.7323) 
(list 3914.585 679.0823) 
(list 3914.585 679.2593) 
(list 3840.5625 678.8093)))
(apply 'command (append '("pline") coords '("c")))
(setq currobj (ssadd (entlast) currobj))
(setq coords (list 
(list 3840.5625 678.9523) 
(list 3914.585 679.4023) 
(list 3914.585 679.5793) 
(list 3840.5625 679.0293)))
(apply 'command (append '("pline") coords '("c")))
(setq currobj (ssadd (entlast) currobj))
(setq coords (list 
(list 3840.5625 679.1723) 
(list 3914.585 679.7223) 
(list 3914.585 679.8993) 
(list 3840.5625 679.2493)))
(apply 'command (append '("pline") coords '("c")))
(setq currobj (ssadd (entlast) currobj))
(setq coords (list 
(list 3840.5625 679.3923) 
(list 3914.585 680.0423) 
(list 3914.585 680.2193) 
(list 3840.5625 679.4693)))
(apply 'command (append '("pline") coords '("c")))
(setq currobj (ssadd (entlast) currobj))
(setq coords (list 
(list 3839.4375 679.4693) 
(list 3765.415 680.2193) 
(list 3765.415 680.0423) 
(list 3839.4375 679.3923)))
(apply 'command (append '("pline") coords '("c")))
(setq currobj (ssadd (entlast) currobj))
(setq coords (list 
(list 3839.4375 679.2493) 
(list 3765.415 679.8993) 
(list 3765.415 679.7223) 
(list 3839.4375 679.1723)))
(apply 'command (append '("pline") coords '("c")))
(setq currobj (ssadd (entlast) currobj))
(setq coords (list 
(list 3839.4375 679.0293) 
(list 3765.415 679.5793) 
(list 3765.415 679.4023) 
(list 3839.4375 678.9523)))
(apply 'command (append '("pline") coords '("c")))
(setq currobj (ssadd (entlast) currobj))
(setq coords (list 
(list 3839.4375 678.8093) 
(list 3765.415 679.2593) 
(list 3765.415 679.0823) 
(list 3839.4375 678.7323)))
(apply 'command (append '("pline") coords '("c")))
(setq currobj (ssadd (entlast) currobj))
(setq coords (list 
(list 3839.4375 678.5893) 
(list 3765.415 678.9393) 
(list 3765.415 678.7623) 
(list 3839.4375 678.5123)))
(apply 'command (append '("pline") coords '("c")))
(setq currobj (ssadd (entlast) currobj))
(setq coords (list 
(list 3839.4375 678.3693) 
(list 3765.415 678.6193) 
(list 3765.415 678.4423) 
(list 3839.4375 678.2923)))
(apply 'command (append '("pline") coords '("c")))
(setq currobj (ssadd (entlast) currobj))
(setq coords (list 
(list 3839.4375 678.1493) 
(list 3765.415 678.2993) 
(list 3765.415 678.1223) 
(list 3839.4375 678.0723)))
(apply 'command (append '("pline") coords '("c")))
(setq currobj (ssadd (entlast) currobj))
(setq coords (list 
(list 3839.4375 677.9293) 
(list 3765.415 677.9793) 
(list 3765.415 677.8023) 
(list 3839.4375 677.8523)))
(apply 'command (append '("pline") coords '("c")))
(setq currobj (ssadd (entlast) currobj))
(setq coords (list 
(list 3839.4375 677.7093) 
(list 3765.415 677.6593) 
(list 3765.415 677.4823) 
(list 3839.4375 677.6323)))
(apply 'command (append '("pline") coords '("c")))
(setq currobj (ssadd (entlast) currobj))
(setq coords (list 
(list 3839.4375 677.4893) 
(list 3765.415 677.3393) 
(list 3765.415 677.1623) 
(list 3839.4375 677.4123)))
(apply 'command (append '("pline") coords '("c")))
(setq currobj (ssadd (entlast) currobj))
(setq coords (list 
(list 3839.4375 677.2693) 
(list 3765.415 677.0193) 
(list 3765.415 676.8423) 
(list 3839.4375 677.1923)))
(apply 'command (append '("pline") coords '("c")))
(setq currobj (ssadd (entlast) currobj))
(setq coords (list 
(list 3839.4375 677.0493) 
(list 3765.415 676.6993) 
(list 3765.415 676.5223) 
(list 3839.4375 676.9723)))
(apply 'command (append '("pline") coords '("c")))
(setq currobj (ssadd (entlast) currobj))
(setq coords (list 
(list 3839.4375 676.8293) 
(list 3765.415 676.3793) 
(list 3765.415 676.2023) 
(list 3839.4375 676.7523)))
(apply 'command (append '("pline") coords '("c")))
(setq currobj (ssadd (entlast) currobj))
(setq coords (list 
(list 3839.4375 676.6093) 
(list 3765.415 676.0593) 
(list 3765.415 675.8823) 
(list 3839.4375 676.5323)))
(apply 'command (append '("pline") coords '("c")))
(setq currobj (ssadd (entlast) currobj))
(setq coords (list 
(list 3839.4375 676.3893) 
(list 3765.415 675.7393) 
(list 3765.415 675.5623) 
(list 3839.4375 676.3123)))
(apply 'command (append '("pline") coords '("c")))
(setq currobj (ssadd (entlast) currobj))
(command "_layer" "set" "nitride" "")
(command "_layer" "set" "text" "")
(command "_circle" "3839.0625,665.1693" "0.075")
(command "_circle" "3839.0625,665.4693" "0.075")
(command "_circle" "3839.0625,665.7693" "0.075")
(command "_circle" "3839.0625,666.0693" "0.075")
(command "_circle" "3839.0625,666.3693" "0.075")
(command "_circle" "3838.7625,665.1693" "0.075")
(command "_circle" "3838.7625,665.4693" "0.075")
(command "_circle" "3838.7625,665.7693" "0.075")
(command "_circle" "3838.7625,666.0693" "0.075")
(command "_circle" "3838.7625,666.3693" "0.075")
(command "_circle" "3838.4625,665.1693" "0.075")
(command "_circle" "3838.4625,665.4693" "0.075")
(command "_circle" "3838.4625,665.7693" "0.075")
(command "_circle" "3838.4625,666.0693" "0.075")
(command "_circle" "3838.4625,666.3693" "0.075")
(command "_circle" "3838.1625,665.1693" "0.075")
(command "_circle" "3838.1625,665.4693" "0.075")
(command "_circle" "3838.1625,665.7693" "0.075")
(command "_circle" "3838.1625,666.0693" "0.075")
(command "_circle" "3838.1625,666.3693" "0.075")
(command "_circle" "3837.8625,665.1693" "0.075")
(command "_circle" "3837.8625,665.4693" "0.075")
(command "_circle" "3837.8625,665.7693" "0.075")
(command "_circle" "3837.8625,666.0693" "0.075")
(command "_circle" "3837.8625,666.3693" "0.075")
(command "_layer" "set" "nitride" "")
(setq coords (list 
(list 3840.2625 690.6123) 
(list 3840.2625 806.257) 
(list 3839.7375 806.257) 
(list 3839.7375 690.6123)))
(apply 'command (append '("pline") coords '("c")))
(setq currobj (ssadd (entlast) currobj))
(command "_layer" "set" "prebias" "")
(command "_rectangle" "3839.7375,690.6123" "3840.2625,806.257")
(setq currobj (ssadd (entlast) currobj))
(command "_layer" "set" "nitride" "")
(setq coords (list 
(list 3840.2625 806.257) 
(list 3840.5625 816.257) 
(list 3840.5625 816.257) 
(list 3840.5625 817.257) 
(list 3914.585 816.507) 
(list 3914.585 821.45) 
(list 3840.5625 820.7) 
(list 3840.5625 821.7) 
(list 3840.5625 821.7) 
(list 3840.2625 831.7) 
(list 3839.7375 831.7) 
(list 3839.4375 821.7) 
(list 3839.4375 821.7) 
(list 3839.4375 820.7) 
(list 3765.415 821.45) 
(list 3765.415 816.507) 
(list 3839.4375 817.257) 
(list 3839.4375 816.257) 
(list 3839.4375 816.257) 
(list 3839.7375 806.257)))
(apply 'command (append '("pline") coords '("c")))
(setq currobj (ssadd (entlast) currobj))
(command "_layer" "set" "prebias" "")
(setq coords (list 
(list 3839.4375 806.257) 
(list 3839.4375 817.257) 
(list 3765.415 816.507) 
(list 3765.415 821.45) 
(list 3839.4375 820.7) 
(list 3839.4375 831.7) 
(list 3840.5625 831.7) 
(list 3840.5625 820.7) 
(list 3914.585 821.45) 
(list 3914.585 816.507) 
(list 3840.5625 817.257) 
(list 3840.5625 806.257)))
(apply 'command (append '("pline") coords '("c")))
(setq currobj (ssadd (entlast) currobj))
(command "_layer" "set" "nitride" "")
(command "_layer" "set" "fda1" "")
(setq coords (list 
(list 3840.5625 817.4) 
(list 3914.585 816.65) 
(list 3914.585 816.827) 
(list 3840.5625 817.477)))
(apply 'command (append '("pline") coords '("c")))
(setq currobj (ssadd (entlast) currobj))
(setq coords (list 
(list 3840.5625 817.62) 
(list 3914.585 816.97) 
(list 3914.585 817.147) 
(list 3840.5625 817.697)))
(apply 'command (append '("pline") coords '("c")))
(setq currobj (ssadd (entlast) currobj))
(setq coords (list 
(list 3840.5625 817.84) 
(list 3914.585 817.29) 
(list 3914.585 817.467) 
(list 3840.5625 817.917)))
(apply 'command (append '("pline") coords '("c")))
(setq currobj (ssadd (entlast) currobj))
(setq coords (list 
(list 3840.5625 818.06) 
(list 3914.585 817.61) 
(list 3914.585 817.787) 
(list 3840.5625 818.137)))
(apply 'command (append '("pline") coords '("c")))
(setq currobj (ssadd (entlast) currobj))
(setq coords (list 
(list 3840.5625 818.28) 
(list 3914.585 817.93) 
(list 3914.585 818.107) 
(list 3840.5625 818.357)))
(apply 'command (append '("pline") coords '("c")))
(setq currobj (ssadd (entlast) currobj))
(setq coords (list 
(list 3840.5625 818.5) 
(list 3914.585 818.25) 
(list 3914.585 818.427) 
(list 3840.5625 818.577)))
(apply 'command (append '("pline") coords '("c")))
(setq currobj (ssadd (entlast) currobj))
(setq coords (list 
(list 3840.5625 818.72) 
(list 3914.585 818.57) 
(list 3914.585 818.747) 
(list 3840.5625 818.797)))
(apply 'command (append '("pline") coords '("c")))
(setq currobj (ssadd (entlast) currobj))
(setq coords (list 
(list 3840.5625 818.94) 
(list 3914.585 818.89) 
(list 3914.585 819.067) 
(list 3840.5625 819.017)))
(apply 'command (append '("pline") coords '("c")))
(setq currobj (ssadd (entlast) currobj))
(setq coords (list 
(list 3840.5625 819.16) 
(list 3914.585 819.21) 
(list 3914.585 819.387) 
(list 3840.5625 819.237)))
(apply 'command (append '("pline") coords '("c")))
(setq currobj (ssadd (entlast) currobj))
(setq coords (list 
(list 3840.5625 819.38) 
(list 3914.585 819.53) 
(list 3914.585 819.707) 
(list 3840.5625 819.457)))
(apply 'command (append '("pline") coords '("c")))
(setq currobj (ssadd (entlast) currobj))
(setq coords (list 
(list 3840.5625 819.6) 
(list 3914.585 819.85) 
(list 3914.585 820.027) 
(list 3840.5625 819.677)))
(apply 'command (append '("pline") coords '("c")))
(setq currobj (ssadd (entlast) currobj))
(setq coords (list 
(list 3840.5625 819.82) 
(list 3914.585 820.17) 
(list 3914.585 820.347) 
(list 3840.5625 819.897)))
(apply 'command (append '("pline") coords '("c")))
(setq currobj (ssadd (entlast) currobj))
(setq coords (list 
(list 3840.5625 820.04) 
(list 3914.585 820.49) 
(list 3914.585 820.667) 
(list 3840.5625 820.117)))
(apply 'command (append '("pline") coords '("c")))
(setq currobj (ssadd (entlast) currobj))
(setq coords (list 
(list 3840.5625 820.26) 
(list 3914.585 820.81) 
(list 3914.585 820.987) 
(list 3840.5625 820.337)))
(apply 'command (append '("pline") coords '("c")))
(setq currobj (ssadd (entlast) currobj))
(setq coords (list 
(list 3840.5625 820.48) 
(list 3914.585 821.13) 
(list 3914.585 821.307) 
(list 3840.5625 820.557)))
(apply 'command (append '("pline") coords '("c")))
(setq currobj (ssadd (entlast) currobj))
(setq coords (list 
(list 3839.4375 820.557) 
(list 3765.415 821.307) 
(list 3765.415 821.13) 
(list 3839.4375 820.48)))
(apply 'command (append '("pline") coords '("c")))
(setq currobj (ssadd (entlast) currobj))
(setq coords (list 
(list 3839.4375 820.337) 
(list 3765.415 820.987) 
(list 3765.415 820.81) 
(list 3839.4375 820.26)))
(apply 'command (append '("pline") coords '("c")))
(setq currobj (ssadd (entlast) currobj))
(setq coords (list 
(list 3839.4375 820.117) 
(list 3765.415 820.667) 
(list 3765.415 820.49) 
(list 3839.4375 820.04)))
(apply 'command (append '("pline") coords '("c")))
(setq currobj (ssadd (entlast) currobj))
(setq coords (list 
(list 3839.4375 819.897) 
(list 3765.415 820.347) 
(list 3765.415 820.17) 
(list 3839.4375 819.82)))
(apply 'command (append '("pline") coords '("c")))
(setq currobj (ssadd (entlast) currobj))
(setq coords (list 
(list 3839.4375 819.677) 
(list 3765.415 820.027) 
(list 3765.415 819.85) 
(list 3839.4375 819.6)))
(apply 'command (append '("pline") coords '("c")))
(setq currobj (ssadd (entlast) currobj))
(setq coords (list 
(list 3839.4375 819.457) 
(list 3765.415 819.707) 
(list 3765.415 819.53) 
(list 3839.4375 819.38)))
(apply 'command (append '("pline") coords '("c")))
(setq currobj (ssadd (entlast) currobj))
(setq coords (list 
(list 3839.4375 819.237) 
(list 3765.415 819.387) 
(list 3765.415 819.21) 
(list 3839.4375 819.16)))
(apply 'command (append '("pline") coords '("c")))
(setq currobj (ssadd (entlast) currobj))
(setq coords (list 
(list 3839.4375 819.017) 
(list 3765.415 819.067) 
(list 3765.415 818.89) 
(list 3839.4375 818.94)))
(apply 'command (append '("pline") coords '("c")))
(setq currobj (ssadd (entlast) currobj))
(setq coords (list 
(list 3839.4375 818.797) 
(list 3765.415 818.747) 
(list 3765.415 818.57) 
(list 3839.4375 818.72)))
(apply 'command (append '("pline") coords '("c")))
(setq currobj (ssadd (entlast) currobj))
(setq coords (list 
(list 3839.4375 818.577) 
(list 3765.415 818.427) 
(list 3765.415 818.25) 
(list 3839.4375 818.5)))
(apply 'command (append '("pline") coords '("c")))
(setq currobj (ssadd (entlast) currobj))
(setq coords (list 
(list 3839.4375 818.357) 
(list 3765.415 818.107) 
(list 3765.415 817.93) 
(list 3839.4375 818.28)))
(apply 'command (append '("pline") coords '("c")))
(setq currobj (ssadd (entlast) currobj))
(setq coords (list 
(list 3839.4375 818.137) 
(list 3765.415 817.787) 
(list 3765.415 817.61) 
(list 3839.4375 818.06)))
(apply 'command (append '("pline") coords '("c")))
(setq currobj (ssadd (entlast) currobj))
(setq coords (list 
(list 3839.4375 817.917) 
(list 3765.415 817.467) 
(list 3765.415 817.29) 
(list 3839.4375 817.84)))
(apply 'command (append '("pline") coords '("c")))
(setq currobj (ssadd (entlast) currobj))
(setq coords (list 
(list 3839.4375 817.697) 
(list 3765.415 817.147) 
(list 3765.415 816.97) 
(list 3839.4375 817.62)))
(apply 'command (append '("pline") coords '("c")))
(setq currobj (ssadd (entlast) currobj))
(setq coords (list 
(list 3839.4375 817.477) 
(list 3765.415 816.827) 
(list 3765.415 816.65) 
(list 3839.4375 817.4)))
(apply 'command (append '("pline") coords '("c")))
(setq currobj (ssadd (entlast) currobj))
(command "_layer" "set" "nitride" "")
(command "_layer" "set" "text" "")
(command "_circle" "3839.0625,806.257" "0.075")
(command "_circle" "3839.0625,806.557" "0.075")
(command "_circle" "3839.0625,806.857" "0.075")
(command "_circle" "3839.0625,807.157" "0.075")
(command "_circle" "3839.0625,807.457" "0.075")
(command "_circle" "3838.7625,806.257" "0.075")
(command "_circle" "3838.7625,806.557" "0.075")
(command "_circle" "3838.7625,806.857" "0.075")
(command "_circle" "3838.7625,807.157" "0.075")
(command "_circle" "3838.7625,807.457" "0.075")
(command "_circle" "3838.4625,806.257" "0.075")
(command "_circle" "3838.4625,806.557" "0.075")
(command "_circle" "3838.4625,806.857" "0.075")
(command "_circle" "3838.4625,807.157" "0.075")
(command "_circle" "3838.4625,807.457" "0.075")
(command "_circle" "3838.1625,806.257" "0.075")
(command "_circle" "3838.1625,806.557" "0.075")
(command "_circle" "3838.1625,806.857" "0.075")
(command "_circle" "3838.1625,807.157" "0.075")
(command "_circle" "3838.1625,807.457" "0.075")
(command "_circle" "3837.8625,806.257" "0.075")
(command "_circle" "3837.8625,806.557" "0.075")
(command "_circle" "3837.8625,806.857" "0.075")
(command "_circle" "3837.8625,807.157" "0.075")
(command "_circle" "3837.8625,807.457" "0.075")
(command "_layer" "set" "nitride" "")
(setq coords (list 
(list 3840.2625 831.7) 
(list 3840.2625 836.7) 
(list 3839.7375 836.7) 
(list 3839.7375 831.7)))
(apply 'command (append '("pline") coords '("c")))
(setq currobj (ssadd (entlast) currobj))
(command "_layer" "set" "prebias" "")
(command "_rectangle" "3839.7375,831.7" "3840.2625,836.7")
(setq currobj (ssadd (entlast) currobj))
(command "_layer" "set" "nitride" "")
(setq cooledsinglenanobeam12 currobj)
(setq currobj nil)
(setq currobj (ssadd))
; DRAWING PHOTONIC CRYSTAL
(command "_layer" "set" "negYjunc" "")
(setq coords (list 
(list 3840.135 866.7) 
(list 3840 851.7) 
(list 3840 866.7)))
(apply 'command (append '("pline") coords '("c")))
(setq currobj (ssadd (entlast) currobj))
(setq coords (list 
(list 3840.2625 836.7) 
(list 3840.415 866.7) 
(list 3841.133 866.7) 
(list 3841.133 836.7)))
(apply 'command (append '("pline") coords '("c")))
(setq currobj (ssadd (entlast) currobj))
(setq coords (list 
(list 3839.865 866.7) 
(list 3840 851.7) 
(list 3840 866.7)))
(apply 'command (append '("pline") coords '("c")))
(setq currobj (ssadd (entlast) currobj))
(setq coords (list 
(list 3839.7375 836.7) 
(list 3839.585 866.7) 
(list 3838.867 866.7) 
(list 3838.867 836.7)))
(apply 'command (append '("pline") coords '("c")))
(setq currobj (ssadd (entlast) currobj))
(command "_layer" "set" "nitride" "")
(setq yjunction12 currobj)
(setq currobj nil)
(setq currobj (ssadd))
(setq tap12 nil)
(setq tap12 (ssadd))
(command "_layer" "set" "phc" "")
(setq coords (list 
(list 3840 866.7) 
(list 3840.135 866.7) 
(list 3840.135 866.7103) 
(list 3840.135 866.7206) 
(list 3840.135 866.7308) 
(list 3840.135 866.7411) 
(list 3840.135 866.7514) 
(list 3840.135 866.7617) 
(list 3840.135 866.7719) 
(list 3840.135 866.7822) 
(list 3840.135 866.7925) 
(list 3840.135 866.8028) 
(list 3840.135 866.8131) 
(list 3840.135 866.8233) 
(list 3840.135 866.8336) 
(list 3840.135 866.8439) 
(list 3840.135 866.8542) 
(list 3840.135 866.8644) 
(list 3840.135 866.8747) 
(list 3840.135 866.885) 
(list 3840.135 866.8953) 
(list 3840.135 866.9056) 
(list 3840.135 866.9158) 
(list 3840.135 866.9261) 
(list 3840.135 866.9364) 
(list 3840.135 866.9467) 
(list 3840.135 866.9569) 
(list 3840.135 866.9672) 
(list 3840.135 866.9775) 
(list 3840.135 866.9878) 
(list 3840.135 866.9981) 
(list 3840.135 867.0083) 
(list 3840.135 867.0186) 
(list 3840.135 867.0289) 
(list 3840.135 867.0392) 
(list 3840.135 867.0494) 
(list 3840.135 867.0597) 
(list 3840.135 867.07) 
(list 3840 867.07)))
(apply 'command (append '("pline") coords '("c")))
(setq tap12 (ssadd (entlast) tap12))
(command "_mirror" (entlast) "" "3840,900" "3840,901" "No")
(setq tap12 (ssadd (entlast) tap12))
(setq coords (list 
(list 3840.4251 866.7) 
(list 3840.415 866.7) 
(list 3840.4153 866.7103) 
(list 3840.4155 866.7206) 
(list 3840.4157 866.7308) 
(list 3840.4159 866.7411) 
(list 3840.416 866.7514) 
(list 3840.4159 866.7617) 
(list 3840.4158 866.7719) 
(list 3840.4156 866.7822) 
(list 3840.4153 866.7925) 
(list 3840.4149 866.8028) 
(list 3840.4144 866.8131) 
(list 3840.4138 866.8233) 
(list 3840.4133 866.8336) 
(list 3840.4127 866.8439) 
(list 3840.4122 866.8542) 
(list 3840.4117 866.8644) 
(list 3840.4113 866.8747) 
(list 3840.411 866.885) 
(list 3840.4109 866.8953) 
(list 3840.4109 866.9056) 
(list 3840.4111 866.9158) 
(list 3840.4114 866.9261) 
(list 3840.412 866.9364) 
(list 3840.4127 866.9467) 
(list 3840.4136 866.9569) 
(list 3840.4146 866.9672) 
(list 3840.4158 866.9775) 
(list 3840.4171 866.9878) 
(list 3840.4183 866.9981) 
(list 3840.4197 867.0083) 
(list 3840.4209 867.0186) 
(list 3840.4221 867.0289) 
(list 3840.4231 867.0392) 
(list 3840.424 867.0494) 
(list 3840.4247 867.0597) 
(list 3840.4251 867.07) 
(list 3840.4251 867.07)))
(apply 'command (append '("pline") coords '("c")))
(setq tap12 (ssadd (entlast) tap12))
(command "_mirror" (entlast) "" "3840,900" "3840,901" "No")
(setq tap12 (ssadd (entlast) tap12))
(setq coords (list 
(list 3841.133 866.7) 
(list 3840.4251 866.7) 
(list 3840.4251 866.7103) 
(list 3840.4251 866.7206) 
(list 3840.4251 866.7308) 
(list 3840.4251 866.7411) 
(list 3840.4251 866.7514) 
(list 3840.4251 866.7617) 
(list 3840.4251 866.7719) 
(list 3840.4251 866.7822) 
(list 3840.4251 866.7925) 
(list 3840.4251 866.8028) 
(list 3840.4251 866.8131) 
(list 3840.4251 866.8233) 
(list 3840.4251 866.8336) 
(list 3840.4251 866.8439) 
(list 3840.4251 866.8542) 
(list 3840.4251 866.8644) 
(list 3840.4251 866.8747) 
(list 3840.4251 866.885) 
(list 3840.4251 866.8953) 
(list 3840.4251 866.9056) 
(list 3840.4251 866.9158) 
(list 3840.4251 866.9261) 
(list 3840.4251 866.9364) 
(list 3840.4251 866.9467) 
(list 3840.4251 866.9569) 
(list 3840.4251 866.9672) 
(list 3840.4251 866.9775) 
(list 3840.4251 866.9878) 
(list 3840.4251 866.9981) 
(list 3840.4251 867.0083) 
(list 3840.4251 867.0186) 
(list 3840.4251 867.0289) 
(list 3840.4251 867.0392) 
(list 3840.4251 867.0494) 
(list 3840.4251 867.0597) 
(list 3840.4251 867.07) 
(list 3841.133 867.07)))
(apply 'command (append '("pline") coords '("c")))
(setq tap12 (ssadd (entlast) tap12))
(command "_mirror" (entlast) "" "3840,900" "3840,901" "No")
(setq tap12 (ssadd (entlast) tap12))
(setq coords (list 
(list 3840 867.07) 
(list 3840.135 867.07) 
(list 3840.135 867.0803) 
(list 3840.135 867.0906) 
(list 3840.135 867.1008) 
(list 3840.135 867.1111) 
(list 3840.135 867.1214) 
(list 3840.135 867.1317) 
(list 3840.135 867.1419) 
(list 3840.135 867.1522) 
(list 3840.135 867.1625) 
(list 3840.135 867.1728) 
(list 3840.135 867.1831) 
(list 3840.135 867.1933) 
(list 3840.135 867.2036) 
(list 3840.135 867.2139) 
(list 3840.135 867.2242) 
(list 3840.135 867.2344) 
(list 3840.135 867.2447) 
(list 3840.135 867.255) 
(list 3840.135 867.2653) 
(list 3840.135 867.2756) 
(list 3840.135 867.2858) 
(list 3840.135 867.2961) 
(list 3840.135 867.3064) 
(list 3840.135 867.3167) 
(list 3840.135 867.3269) 
(list 3840.135 867.3372) 
(list 3840.135 867.3475) 
(list 3840.135 867.3578) 
(list 3840.135 867.3681) 
(list 3840.135 867.3783) 
(list 3840.135 867.3886) 
(list 3840.135 867.3989) 
(list 3840.135 867.4092) 
(list 3840.135 867.4194) 
(list 3840.135 867.4297) 
(list 3840.135 867.44) 
(list 3840 867.44)))
(apply 'command (append '("pline") coords '("c")))
(setq tap12 (ssadd (entlast) tap12))
(command "_mirror" (entlast) "" "3840,900" "3840,901" "No")
(setq tap12 (ssadd (entlast) tap12))
(setq coords (list 
(list 3840.4352 867.07) 
(list 3840.4251 867.07) 
(list 3840.4252 867.0803) 
(list 3840.4251 867.0906) 
(list 3840.4246 867.1008) 
(list 3840.4239 867.1111) 
(list 3840.4228 867.1214) 
(list 3840.4215 867.1317) 
(list 3840.42 867.1419) 
(list 3840.4182 867.1522) 
(list 3840.4163 867.1625) 
(list 3840.4144 867.1728) 
(list 3840.4124 867.1831) 
(list 3840.4104 867.1933) 
(list 3840.4085 867.2036) 
(list 3840.4069 867.2139) 
(list 3840.4054 867.2242) 
(list 3840.4043 867.2344) 
(list 3840.4035 867.2447) 
(list 3840.403 867.255) 
(list 3840.403 867.2653) 
(list 3840.4035 867.2756) 
(list 3840.4043 867.2858) 
(list 3840.4056 867.2961) 
(list 3840.4072 867.3064) 
(list 3840.4093 867.3167) 
(list 3840.4116 867.3269) 
(list 3840.4141 867.3372) 
(list 3840.4169 867.3475) 
(list 3840.4197 867.3578) 
(list 3840.4225 867.3681) 
(list 3840.4252 867.3783) 
(list 3840.4278 867.3886) 
(list 3840.4301 867.3989) 
(list 3840.432 867.4092) 
(list 3840.4336 867.4194) 
(list 3840.4346 867.4297) 
(list 3840.4352 867.44) 
(list 3840.4352 867.44)))
(apply 'command (append '("pline") coords '("c")))
(setq tap12 (ssadd (entlast) tap12))
(command "_mirror" (entlast) "" "3840,900" "3840,901" "No")
(setq tap12 (ssadd (entlast) tap12))
(setq coords (list 
(list 3841.133 867.07) 
(list 3840.4352 867.07) 
(list 3840.4352 867.0803) 
(list 3840.4352 867.0906) 
(list 3840.4352 867.1008) 
(list 3840.4352 867.1111) 
(list 3840.4352 867.1214) 
(list 3840.4352 867.1317) 
(list 3840.4352 867.1419) 
(list 3840.4352 867.1522) 
(list 3840.4352 867.1625) 
(list 3840.4352 867.1728) 
(list 3840.4352 867.1831) 
(list 3840.4352 867.1933) 
(list 3840.4352 867.2036) 
(list 3840.4352 867.2139) 
(list 3840.4352 867.2242) 
(list 3840.4352 867.2344) 
(list 3840.4352 867.2447) 
(list 3840.4352 867.255) 
(list 3840.4352 867.2653) 
(list 3840.4352 867.2756) 
(list 3840.4352 867.2858) 
(list 3840.4352 867.2961) 
(list 3840.4352 867.3064) 
(list 3840.4352 867.3167) 
(list 3840.4352 867.3269) 
(list 3840.4352 867.3372) 
(list 3840.4352 867.3475) 
(list 3840.4352 867.3578) 
(list 3840.4352 867.3681) 
(list 3840.4352 867.3783) 
(list 3840.4352 867.3886) 
(list 3840.4352 867.3989) 
(list 3840.4352 867.4092) 
(list 3840.4352 867.4194) 
(list 3840.4352 867.4297) 
(list 3840.4352 867.44) 
(list 3841.133 867.44)))
(apply 'command (append '("pline") coords '("c")))
(setq tap12 (ssadd (entlast) tap12))
(command "_mirror" (entlast) "" "3840,900" "3840,901" "No")
(setq tap12 (ssadd (entlast) tap12))
(setq coords (list 
(list 3840 867.44) 
(list 3840.135 867.44) 
(list 3840.135 867.4503) 
(list 3840.135 867.4606) 
(list 3840.135 867.4708) 
(list 3840.135 867.4811) 
(list 3840.135 867.4914) 
(list 3840.135 867.5017) 
(list 3840.135 867.5119) 
(list 3840.135 867.5222) 
(list 3840.135 867.5325) 
(list 3840.135 867.5428) 
(list 3840.135 867.5531) 
(list 3840.135 867.5633) 
(list 3840.135 867.5736) 
(list 3840.135 867.5839) 
(list 3840.135 867.5942) 
(list 3840.135 867.6044) 
(list 3840.135 867.6147) 
(list 3840.135 867.625) 
(list 3840.135 867.6353) 
(list 3840.135 867.6456) 
(list 3840.135 867.6558) 
(list 3840.135 867.6661) 
(list 3840.135 867.6764) 
(list 3840.135 867.6867) 
(list 3840.135 867.6969) 
(list 3840.135 867.7072) 
(list 3840.135 867.7175) 
(list 3840.135 867.7278) 
(list 3840.135 867.7381) 
(list 3840.135 867.7483) 
(list 3840.135 867.7586) 
(list 3840.135 867.7689) 
(list 3840.135 867.7792) 
(list 3840.135 867.7894) 
(list 3840.135 867.7997) 
(list 3840.135 867.81) 
(list 3840 867.81)))
(apply 'command (append '("pline") coords '("c")))
(setq tap12 (ssadd (entlast) tap12))
(command "_mirror" (entlast) "" "3840,900" "3840,901" "No")
(setq tap12 (ssadd (entlast) tap12))
(setq coords (list 
(list 3840.4453 867.44) 
(list 3840.4352 867.44) 
(list 3840.4352 867.4503) 
(list 3840.4346 867.4606) 
(list 3840.4335 867.4708) 
(list 3840.4319 867.4811) 
(list 3840.4297 867.4914) 
(list 3840.4271 867.5017) 
(list 3840.4241 867.5119) 
(list 3840.4209 867.5222) 
(list 3840.4174 867.5325) 
(list 3840.4139 867.5428) 
(list 3840.4103 867.5531) 
(list 3840.407 867.5633) 
(list 3840.4038 867.5736) 
(list 3840.401 867.5839) 
(list 3840.3987 867.5942) 
(list 3840.3969 867.6044) 
(list 3840.3956 867.6147) 
(list 3840.3951 867.625) 
(list 3840.3952 867.6353) 
(list 3840.396 867.6456) 
(list 3840.3975 867.6558) 
(list 3840.3997 867.6661) 
(list 3840.4025 867.6764) 
(list 3840.4058 867.6867) 
(list 3840.4095 867.6969) 
(list 3840.4136 867.7072) 
(list 3840.4179 867.7175) 
(list 3840.4223 867.7278) 
(list 3840.4267 867.7381) 
(list 3840.4308 867.7483) 
(list 3840.4347 867.7586) 
(list 3840.4381 867.7689) 
(list 3840.4409 867.7792) 
(list 3840.4431 867.7894) 
(list 3840.4446 867.7997) 
(list 3840.4453 867.81) 
(list 3840.4453 867.81)))
(apply 'command (append '("pline") coords '("c")))
(setq tap12 (ssadd (entlast) tap12))
(command "_mirror" (entlast) "" "3840,900" "3840,901" "No")
(setq tap12 (ssadd (entlast) tap12))
(setq coords (list 
(list 3841.133 867.44) 
(list 3840.4453 867.44) 
(list 3840.4453 867.4503) 
(list 3840.4453 867.4606) 
(list 3840.4453 867.4708) 
(list 3840.4453 867.4811) 
(list 3840.4453 867.4914) 
(list 3840.4453 867.5017) 
(list 3840.4453 867.5119) 
(list 3840.4453 867.5222) 
(list 3840.4453 867.5325) 
(list 3840.4453 867.5428) 
(list 3840.4453 867.5531) 
(list 3840.4453 867.5633) 
(list 3840.4453 867.5736) 
(list 3840.4453 867.5839) 
(list 3840.4453 867.5942) 
(list 3840.4453 867.6044) 
(list 3840.4453 867.6147) 
(list 3840.4453 867.625) 
(list 3840.4453 867.6353) 
(list 3840.4453 867.6456) 
(list 3840.4453 867.6558) 
(list 3840.4453 867.6661) 
(list 3840.4453 867.6764) 
(list 3840.4453 867.6867) 
(list 3840.4453 867.6969) 
(list 3840.4453 867.7072) 
(list 3840.4453 867.7175) 
(list 3840.4453 867.7278) 
(list 3840.4453 867.7381) 
(list 3840.4453 867.7483) 
(list 3840.4453 867.7586) 
(list 3840.4453 867.7689) 
(list 3840.4453 867.7792) 
(list 3840.4453 867.7894) 
(list 3840.4453 867.7997) 
(list 3840.4453 867.81) 
(list 3841.133 867.81)))
(apply 'command (append '("pline") coords '("c")))
(setq tap12 (ssadd (entlast) tap12))
(command "_mirror" (entlast) "" "3840,900" "3840,901" "No")
(setq tap12 (ssadd (entlast) tap12))
(setq coords (list 
(list 3840 867.81) 
(list 3840.135 867.81) 
(list 3840.135 867.8203) 
(list 3840.135 867.8306) 
(list 3840.135 867.8408) 
(list 3840.135 867.8511) 
(list 3840.135 867.8614) 
(list 3840.135 867.8717) 
(list 3840.135 867.8819) 
(list 3840.135 867.8922) 
(list 3840.135 867.9025) 
(list 3840.135 867.9128) 
(list 3840.135 867.9231) 
(list 3840.135 867.9333) 
(list 3840.135 867.9436) 
(list 3840.135 867.9539) 
(list 3840.135 867.9642) 
(list 3840.135 867.9744) 
(list 3840.135 867.9847) 
(list 3840.135 867.995) 
(list 3840.135 868.0053) 
(list 3840.135 868.0156) 
(list 3840.135 868.0258) 
(list 3840.135 868.0361) 
(list 3840.135 868.0464) 
(list 3840.135 868.0567) 
(list 3840.135 868.0669) 
(list 3840.135 868.0772) 
(list 3840.135 868.0875) 
(list 3840.135 868.0978) 
(list 3840.135 868.1081) 
(list 3840.135 868.1183) 
(list 3840.135 868.1286) 
(list 3840.135 868.1389) 
(list 3840.135 868.1492) 
(list 3840.135 868.1594) 
(list 3840.135 868.1697) 
(list 3840.135 868.18) 
(list 3840 868.18)))
(apply 'command (append '("pline") coords '("c")))
(setq tap12 (ssadd (entlast) tap12))
(command "_mirror" (entlast) "" "3840,900" "3840,901" "No")
(setq tap12 (ssadd (entlast) tap12))
(setq coords (list 
(list 3840.4554 867.81) 
(list 3840.4453 867.81) 
(list 3840.4452 867.8203) 
(list 3840.4442 867.8306) 
(list 3840.4424 867.8408) 
(list 3840.4398 867.8511) 
(list 3840.4366 867.8614) 
(list 3840.4327 867.8717) 
(list 3840.4283 867.8819) 
(list 3840.4235 867.8922) 
(list 3840.4185 867.9025) 
(list 3840.4134 867.9128) 
(list 3840.4083 867.9231) 
(list 3840.4035 867.9333) 
(list 3840.3991 867.9436) 
(list 3840.3952 867.9539) 
(list 3840.3919 867.9642) 
(list 3840.3894 867.9744) 
(list 3840.3878 867.9847) 
(list 3840.3871 867.995) 
(list 3840.3874 868.0053) 
(list 3840.3886 868.0156) 
(list 3840.3908 868.0258) 
(list 3840.3939 868.0361) 
(list 3840.3978 868.0464) 
(list 3840.4023 868.0567) 
(list 3840.4075 868.0669) 
(list 3840.4131 868.0772) 
(list 3840.419 868.0875) 
(list 3840.425 868.0978) 
(list 3840.4308 868.1081) 
(list 3840.4364 868.1183) 
(list 3840.4415 868.1286) 
(list 3840.4461 868.1389) 
(list 3840.4498 868.1492) 
(list 3840.4527 868.1594) 
(list 3840.4546 868.1697) 
(list 3840.4554 868.18) 
(list 3840.4554 868.18)))
(apply 'command (append '("pline") coords '("c")))
(setq tap12 (ssadd (entlast) tap12))
(command "_mirror" (entlast) "" "3840,900" "3840,901" "No")
(setq tap12 (ssadd (entlast) tap12))
(setq coords (list 
(list 3841.133 867.81) 
(list 3840.4554 867.81) 
(list 3840.4554 867.8203) 
(list 3840.4554 867.8306) 
(list 3840.4554 867.8408) 
(list 3840.4554 867.8511) 
(list 3840.4554 867.8614) 
(list 3840.4554 867.8717) 
(list 3840.4554 867.8819) 
(list 3840.4554 867.8922) 
(list 3840.4554 867.9025) 
(list 3840.4554 867.9128) 
(list 3840.4554 867.9231) 
(list 3840.4554 867.9333) 
(list 3840.4554 867.9436) 
(list 3840.4554 867.9539) 
(list 3840.4554 867.9642) 
(list 3840.4554 867.9744) 
(list 3840.4554 867.9847) 
(list 3840.4554 867.995) 
(list 3840.4554 868.0053) 
(list 3840.4554 868.0156) 
(list 3840.4554 868.0258) 
(list 3840.4554 868.0361) 
(list 3840.4554 868.0464) 
(list 3840.4554 868.0567) 
(list 3840.4554 868.0669) 
(list 3840.4554 868.0772) 
(list 3840.4554 868.0875) 
(list 3840.4554 868.0978) 
(list 3840.4554 868.1081) 
(list 3840.4554 868.1183) 
(list 3840.4554 868.1286) 
(list 3840.4554 868.1389) 
(list 3840.4554 868.1492) 
(list 3840.4554 868.1594) 
(list 3840.4554 868.1697) 
(list 3840.4554 868.18) 
(list 3841.133 868.18)))
(apply 'command (append '("pline") coords '("c")))
(setq tap12 (ssadd (entlast) tap12))
(command "_mirror" (entlast) "" "3840,900" "3840,901" "No")
(setq tap12 (ssadd (entlast) tap12))
(setq coords (list 
(list 3840 868.18) 
(list 3840.135 868.18) 
(list 3840.135 868.1903) 
(list 3840.135 868.2006) 
(list 3840.135 868.2108) 
(list 3840.135 868.2211) 
(list 3840.135 868.2314) 
(list 3840.135 868.2417) 
(list 3840.135 868.2519) 
(list 3840.135 868.2622) 
(list 3840.135 868.2725) 
(list 3840.135 868.2828) 
(list 3840.135 868.2931) 
(list 3840.135 868.3033) 
(list 3840.135 868.3136) 
(list 3840.135 868.3239) 
(list 3840.135 868.3342) 
(list 3840.135 868.3444) 
(list 3840.135 868.3547) 
(list 3840.135 868.365) 
(list 3840.135 868.3753) 
(list 3840.135 868.3856) 
(list 3840.135 868.3958) 
(list 3840.135 868.4061) 
(list 3840.135 868.4164) 
(list 3840.135 868.4267) 
(list 3840.135 868.4369) 
(list 3840.135 868.4472) 
(list 3840.135 868.4575) 
(list 3840.135 868.4678) 
(list 3840.135 868.4781) 
(list 3840.135 868.4883) 
(list 3840.135 868.4986) 
(list 3840.135 868.5089) 
(list 3840.135 868.5192) 
(list 3840.135 868.5294) 
(list 3840.135 868.5397) 
(list 3840.135 868.55) 
(list 3840 868.55)))
(apply 'command (append '("pline") coords '("c")))
(setq tap12 (ssadd (entlast) tap12))
(command "_mirror" (entlast) "" "3840,900" "3840,901" "No")
(setq tap12 (ssadd (entlast) tap12))
(setq coords (list 
(list 3840.4655 868.18) 
(list 3840.4554 868.18) 
(list 3840.4551 868.1903) 
(list 3840.4538 868.2006) 
(list 3840.4513 868.2108) 
(list 3840.4478 868.2211) 
(list 3840.4434 868.2314) 
(list 3840.4383 868.2417) 
(list 3840.4324 868.2519) 
(list 3840.4261 868.2622) 
(list 3840.4195 868.2725) 
(list 3840.4129 868.2828) 
(list 3840.4063 868.2931) 
(list 3840.4001 868.3033) 
(list 3840.3943 868.3136) 
(list 3840.3893 868.3239) 
(list 3840.3852 868.3342) 
(list 3840.382 868.3444) 
(list 3840.38 868.3547) 
(list 3840.3792 868.365) 
(list 3840.3796 868.3753) 
(list 3840.3812 868.3856) 
(list 3840.384 868.3958) 
(list 3840.388 868.4061) 
(list 3840.393 868.4164) 
(list 3840.3989 868.4267) 
(list 3840.4055 868.4369) 
(list 3840.4126 868.4472) 
(list 3840.4201 868.4575) 
(list 3840.4276 868.4678) 
(list 3840.435 868.4781) 
(list 3840.442 868.4883) 
(list 3840.4484 868.4986) 
(list 3840.454 868.5089) 
(list 3840.4587 868.5192) 
(list 3840.4622 868.5294) 
(list 3840.4645 868.5397) 
(list 3840.4655 868.55) 
(list 3840.4655 868.55)))
(apply 'command (append '("pline") coords '("c")))
(setq tap12 (ssadd (entlast) tap12))
(command "_mirror" (entlast) "" "3840,900" "3840,901" "No")
(setq tap12 (ssadd (entlast) tap12))
(setq coords (list 
(list 3841.133 868.18) 
(list 3840.4655 868.18) 
(list 3840.4655 868.1903) 
(list 3840.4655 868.2006) 
(list 3840.4655 868.2108) 
(list 3840.4655 868.2211) 
(list 3840.4655 868.2314) 
(list 3840.4655 868.2417) 
(list 3840.4655 868.2519) 
(list 3840.4655 868.2622) 
(list 3840.4655 868.2725) 
(list 3840.4655 868.2828) 
(list 3840.4655 868.2931) 
(list 3840.4655 868.3033) 
(list 3840.4655 868.3136) 
(list 3840.4655 868.3239) 
(list 3840.4655 868.3342) 
(list 3840.4655 868.3444) 
(list 3840.4655 868.3547) 
(list 3840.4655 868.365) 
(list 3840.4655 868.3753) 
(list 3840.4655 868.3856) 
(list 3840.4655 868.3958) 
(list 3840.4655 868.4061) 
(list 3840.4655 868.4164) 
(list 3840.4655 868.4267) 
(list 3840.4655 868.4369) 
(list 3840.4655 868.4472) 
(list 3840.4655 868.4575) 
(list 3840.4655 868.4678) 
(list 3840.4655 868.4781) 
(list 3840.4655 868.4883) 
(list 3840.4655 868.4986) 
(list 3840.4655 868.5089) 
(list 3840.4655 868.5192) 
(list 3840.4655 868.5294) 
(list 3840.4655 868.5397) 
(list 3840.4655 868.55) 
(list 3841.133 868.55)))
(apply 'command (append '("pline") coords '("c")))
(setq tap12 (ssadd (entlast) tap12))
(command "_mirror" (entlast) "" "3840,900" "3840,901" "No")
(setq tap12 (ssadd (entlast) tap12))
(setq coords (list 
(list 3840 868.55) 
(list 3840.135 868.55) 
(list 3840.135 868.5603) 
(list 3840.135 868.5706) 
(list 3840.135 868.5808) 
(list 3840.135 868.5911) 
(list 3840.135 868.6014) 
(list 3840.135 868.6117) 
(list 3840.135 868.6219) 
(list 3840.135 868.6322) 
(list 3840.135 868.6425) 
(list 3840.135 868.6528) 
(list 3840.135 868.6631) 
(list 3840.135 868.6733) 
(list 3840.135 868.6836) 
(list 3840.135 868.6939) 
(list 3840.135 868.7042) 
(list 3840.135 868.7144) 
(list 3840.135 868.7247) 
(list 3840.135 868.735) 
(list 3840.135 868.7453) 
(list 3840.135 868.7556) 
(list 3840.135 868.7658) 
(list 3840.135 868.7761) 
(list 3840.135 868.7864) 
(list 3840.135 868.7967) 
(list 3840.135 868.8069) 
(list 3840.135 868.8172) 
(list 3840.135 868.8275) 
(list 3840.135 868.8378) 
(list 3840.135 868.8481) 
(list 3840.135 868.8583) 
(list 3840.135 868.8686) 
(list 3840.135 868.8789) 
(list 3840.135 868.8892) 
(list 3840.135 868.8994) 
(list 3840.135 868.9097) 
(list 3840.135 868.92) 
(list 3840 868.92)))
(apply 'command (append '("pline") coords '("c")))
(setq tap12 (ssadd (entlast) tap12))
(command "_mirror" (entlast) "" "3840,900" "3840,901" "No")
(setq tap12 (ssadd (entlast) tap12))
(setq coords (list 
(list 3840.4756 868.55) 
(list 3840.4655 868.55) 
(list 3840.4651 868.5603) 
(list 3840.4633 868.5706) 
(list 3840.4602 868.5808) 
(list 3840.4558 868.5911) 
(list 3840.4503 868.6014) 
(list 3840.4438 868.6117) 
(list 3840.4366 868.6219) 
(list 3840.4288 868.6322) 
(list 3840.4206 868.6425) 
(list 3840.4124 868.6528) 
(list 3840.4043 868.6631) 
(list 3840.3966 868.6733) 
(list 3840.3896 868.6836) 
(list 3840.3835 868.6939) 
(list 3840.3784 868.7042) 
(list 3840.3746 868.7144) 
(list 3840.3722 868.7247) 
(list 3840.3712 868.735) 
(list 3840.3717 868.7453) 
(list 3840.3738 868.7556) 
(list 3840.3773 868.7658) 
(list 3840.3822 868.7761) 
(list 3840.3883 868.7864) 
(list 3840.3954 868.7967) 
(list 3840.4035 868.8069) 
(list 3840.4121 868.8172) 
(list 3840.4211 868.8275) 
(list 3840.4302 868.8378) 
(list 3840.4391 868.8481) 
(list 3840.4476 868.8583) 
(list 3840.4553 868.8686) 
(list 3840.462 868.8789) 
(list 3840.4676 868.8892) 
(list 3840.4718 868.8994) 
(list 3840.4745 868.9097) 
(list 3840.4756 868.92) 
(list 3840.4756 868.92)))
(apply 'command (append '("pline") coords '("c")))
(setq tap12 (ssadd (entlast) tap12))
(command "_mirror" (entlast) "" "3840,900" "3840,901" "No")
(setq tap12 (ssadd (entlast) tap12))
(setq coords (list 
(list 3841.133 868.55) 
(list 3840.4756 868.55) 
(list 3840.4756 868.5603) 
(list 3840.4756 868.5706) 
(list 3840.4756 868.5808) 
(list 3840.4756 868.5911) 
(list 3840.4756 868.6014) 
(list 3840.4756 868.6117) 
(list 3840.4756 868.6219) 
(list 3840.4756 868.6322) 
(list 3840.4756 868.6425) 
(list 3840.4756 868.6528) 
(list 3840.4756 868.6631) 
(list 3840.4756 868.6733) 
(list 3840.4756 868.6836) 
(list 3840.4756 868.6939) 
(list 3840.4756 868.7042) 
(list 3840.4756 868.7144) 
(list 3840.4756 868.7247) 
(list 3840.4756 868.735) 
(list 3840.4756 868.7453) 
(list 3840.4756 868.7556) 
(list 3840.4756 868.7658) 
(list 3840.4756 868.7761) 
(list 3840.4756 868.7864) 
(list 3840.4756 868.7967) 
(list 3840.4756 868.8069) 
(list 3840.4756 868.8172) 
(list 3840.4756 868.8275) 
(list 3840.4756 868.8378) 
(list 3840.4756 868.8481) 
(list 3840.4756 868.8583) 
(list 3840.4756 868.8686) 
(list 3840.4756 868.8789) 
(list 3840.4756 868.8892) 
(list 3840.4756 868.8994) 
(list 3840.4756 868.9097) 
(list 3840.4756 868.92) 
(list 3841.133 868.92)))
(apply 'command (append '("pline") coords '("c")))
(setq tap12 (ssadd (entlast) tap12))
(command "_mirror" (entlast) "" "3840,900" "3840,901" "No")
(setq tap12 (ssadd (entlast) tap12))
(setq coords (list 
(list 3840 868.92) 
(list 3840.135 868.92) 
(list 3840.135 868.9303) 
(list 3840.135 868.9406) 
(list 3840.135 868.9508) 
(list 3840.135 868.9611) 
(list 3840.135 868.9714) 
(list 3840.135 868.9817) 
(list 3840.135 868.9919) 
(list 3840.135 869.0022) 
(list 3840.135 869.0125) 
(list 3840.135 869.0228) 
(list 3840.135 869.0331) 
(list 3840.135 869.0433) 
(list 3840.135 869.0536) 
(list 3840.135 869.0639) 
(list 3840.135 869.0742) 
(list 3840.135 869.0844) 
(list 3840.135 869.0947) 
(list 3840.135 869.105) 
(list 3840.135 869.1153) 
(list 3840.135 869.1256) 
(list 3840.135 869.1358) 
(list 3840.135 869.1461) 
(list 3840.135 869.1564) 
(list 3840.135 869.1667) 
(list 3840.135 869.1769) 
(list 3840.135 869.1872) 
(list 3840.135 869.1975) 
(list 3840.135 869.2078) 
(list 3840.135 869.2181) 
(list 3840.135 869.2283) 
(list 3840.135 869.2386) 
(list 3840.135 869.2489) 
(list 3840.135 869.2592) 
(list 3840.135 869.2694) 
(list 3840.135 869.2797) 
(list 3840.135 869.29) 
(list 3840 869.29)))
(apply 'command (append '("pline") coords '("c")))
(setq tap12 (ssadd (entlast) tap12))
(command "_mirror" (entlast) "" "3840,900" "3840,901" "No")
(setq tap12 (ssadd (entlast) tap12))
(setq coords (list 
(list 3840.4857 868.92) 
(list 3840.4756 868.92) 
(list 3840.4751 868.9303) 
(list 3840.4729 868.9406) 
(list 3840.4691 868.9508) 
(list 3840.4638 868.9611) 
(list 3840.4572 868.9714) 
(list 3840.4494 868.9817) 
(list 3840.4407 868.9919) 
(list 3840.4314 869.0022) 
(list 3840.4217 869.0125) 
(list 3840.4118 869.0228) 
(list 3840.4022 869.0331) 
(list 3840.3931 869.0433) 
(list 3840.3848 869.0536) 
(list 3840.3776 869.0639) 
(list 3840.3716 869.0742) 
(list 3840.3672 869.0844) 
(list 3840.3643 869.0947) 
(list 3840.3632 869.105) 
(list 3840.3639 869.1153) 
(list 3840.3663 869.1256) 
(list 3840.3705 869.1358) 
(list 3840.3763 869.1461) 
(list 3840.3835 869.1564) 
(list 3840.392 869.1667) 
(list 3840.4015 869.1769) 
(list 3840.4116 869.1872) 
(list 3840.4222 869.1975) 
(list 3840.4329 869.2078) 
(list 3840.4433 869.2181) 
(list 3840.4532 869.2283) 
(list 3840.4622 869.2386) 
(list 3840.47 869.2489) 
(list 3840.4765 869.2592) 
(list 3840.4814 869.2694) 
(list 3840.4845 869.2797) 
(list 3840.4857 869.29) 
(list 3840.4857 869.29)))
(apply 'command (append '("pline") coords '("c")))
(setq tap12 (ssadd (entlast) tap12))
(command "_mirror" (entlast) "" "3840,900" "3840,901" "No")
(setq tap12 (ssadd (entlast) tap12))
(setq coords (list 
(list 3841.133 868.92) 
(list 3840.4857 868.92) 
(list 3840.4857 868.9303) 
(list 3840.4857 868.9406) 
(list 3840.4857 868.9508) 
(list 3840.4857 868.9611) 
(list 3840.4857 868.9714) 
(list 3840.4857 868.9817) 
(list 3840.4857 868.9919) 
(list 3840.4857 869.0022) 
(list 3840.4857 869.0125) 
(list 3840.4857 869.0228) 
(list 3840.4857 869.0331) 
(list 3840.4857 869.0433) 
(list 3840.4857 869.0536) 
(list 3840.4857 869.0639) 
(list 3840.4857 869.0742) 
(list 3840.4857 869.0844) 
(list 3840.4857 869.0947) 
(list 3840.4857 869.105) 
(list 3840.4857 869.1153) 
(list 3840.4857 869.1256) 
(list 3840.4857 869.1358) 
(list 3840.4857 869.1461) 
(list 3840.4857 869.1564) 
(list 3840.4857 869.1667) 
(list 3840.4857 869.1769) 
(list 3840.4857 869.1872) 
(list 3840.4857 869.1975) 
(list 3840.4857 869.2078) 
(list 3840.4857 869.2181) 
(list 3840.4857 869.2283) 
(list 3840.4857 869.2386) 
(list 3840.4857 869.2489) 
(list 3840.4857 869.2592) 
(list 3840.4857 869.2694) 
(list 3840.4857 869.2797) 
(list 3840.4857 869.29) 
(list 3841.133 869.29)))
(apply 'command (append '("pline") coords '("c")))
(setq tap12 (ssadd (entlast) tap12))
(command "_mirror" (entlast) "" "3840,900" "3840,901" "No")
(setq tap12 (ssadd (entlast) tap12))
(setq coords (list 
(list 3840 869.29) 
(list 3840.135 869.29) 
(list 3840.135 869.3003) 
(list 3840.135 869.3106) 
(list 3840.135 869.3208) 
(list 3840.135 869.3311) 
(list 3840.135 869.3414) 
(list 3840.135 869.3517) 
(list 3840.135 869.3619) 
(list 3840.135 869.3722) 
(list 3840.135 869.3825) 
(list 3840.135 869.3928) 
(list 3840.135 869.4031) 
(list 3840.135 869.4133) 
(list 3840.135 869.4236) 
(list 3840.135 869.4339) 
(list 3840.135 869.4442) 
(list 3840.135 869.4544) 
(list 3840.135 869.4647) 
(list 3840.135 869.475) 
(list 3840.135 869.4853) 
(list 3840.135 869.4956) 
(list 3840.135 869.5058) 
(list 3840.135 869.5161) 
(list 3840.135 869.5264) 
(list 3840.135 869.5367) 
(list 3840.135 869.5469) 
(list 3840.135 869.5572) 
(list 3840.135 869.5675) 
(list 3840.135 869.5778) 
(list 3840.135 869.5881) 
(list 3840.135 869.5983) 
(list 3840.135 869.6086) 
(list 3840.135 869.6189) 
(list 3840.135 869.6292) 
(list 3840.135 869.6394) 
(list 3840.135 869.6497) 
(list 3840.135 869.66) 
(list 3840 869.66)))
(apply 'command (append '("pline") coords '("c")))
(setq tap12 (ssadd (entlast) tap12))
(command "_mirror" (entlast) "" "3840,900" "3840,901" "No")
(setq tap12 (ssadd (entlast) tap12))
(setq coords (list 
(list 3840.4958 869.29) 
(list 3840.4857 869.29) 
(list 3840.485 869.3003) 
(list 3840.4824 869.3106) 
(list 3840.478 869.3208) 
(list 3840.4718 869.3311) 
(list 3840.4641 869.3414) 
(list 3840.455 869.3517) 
(list 3840.4449 869.3619) 
(list 3840.434 869.3722) 
(list 3840.4227 869.3825) 
(list 3840.4113 869.3928) 
(list 3840.4002 869.4031) 
(list 3840.3897 869.4133) 
(list 3840.3801 869.4236) 
(list 3840.3718 869.4339) 
(list 3840.3649 869.4442) 
(list 3840.3597 869.4544) 
(list 3840.3565 869.4647) 
(list 3840.3553 869.475) 
(list 3840.3561 869.4853) 
(list 3840.3589 869.4956) 
(list 3840.3638 869.5058) 
(list 3840.3705 869.5161) 
(list 3840.3788 869.5264) 
(list 3840.3886 869.5367) 
(list 3840.3994 869.5469) 
(list 3840.4111 869.5572) 
(list 3840.4233 869.5675) 
(list 3840.4355 869.5778) 
(list 3840.4474 869.5881) 
(list 3840.4587 869.5983) 
(list 3840.469 869.6086) 
(list 3840.478 869.6189) 
(list 3840.4854 869.6292) 
(list 3840.4909 869.6394) 
(list 3840.4944 869.6497) 
(list 3840.4958 869.66) 
(list 3840.4958 869.66)))
(apply 'command (append '("pline") coords '("c")))
(setq tap12 (ssadd (entlast) tap12))
(command "_mirror" (entlast) "" "3840,900" "3840,901" "No")
(setq tap12 (ssadd (entlast) tap12))
(setq coords (list 
(list 3841.133 869.29) 
(list 3840.4958 869.29) 
(list 3840.4958 869.3003) 
(list 3840.4958 869.3106) 
(list 3840.4958 869.3208) 
(list 3840.4958 869.3311) 
(list 3840.4958 869.3414) 
(list 3840.4958 869.3517) 
(list 3840.4958 869.3619) 
(list 3840.4958 869.3722) 
(list 3840.4958 869.3825) 
(list 3840.4958 869.3928) 
(list 3840.4958 869.4031) 
(list 3840.4958 869.4133) 
(list 3840.4958 869.4236) 
(list 3840.4958 869.4339) 
(list 3840.4958 869.4442) 
(list 3840.4958 869.4544) 
(list 3840.4958 869.4647) 
(list 3840.4958 869.475) 
(list 3840.4958 869.4853) 
(list 3840.4958 869.4956) 
(list 3840.4958 869.5058) 
(list 3840.4958 869.5161) 
(list 3840.4958 869.5264) 
(list 3840.4958 869.5367) 
(list 3840.4958 869.5469) 
(list 3840.4958 869.5572) 
(list 3840.4958 869.5675) 
(list 3840.4958 869.5778) 
(list 3840.4958 869.5881) 
(list 3840.4958 869.5983) 
(list 3840.4958 869.6086) 
(list 3840.4958 869.6189) 
(list 3840.4958 869.6292) 
(list 3840.4958 869.6394) 
(list 3840.4958 869.6497) 
(list 3840.4958 869.66) 
(list 3841.133 869.66)))
(apply 'command (append '("pline") coords '("c")))
(setq tap12 (ssadd (entlast) tap12))
(command "_mirror" (entlast) "" "3840,900" "3840,901" "No")
(setq tap12 (ssadd (entlast) tap12))
(setq coords (list 
(list 3840 869.66) 
(list 3840.135 869.66) 
(list 3840.135 869.6703) 
(list 3840.135 869.6806) 
(list 3840.135 869.6908) 
(list 3840.135 869.7011) 
(list 3840.135 869.7114) 
(list 3840.135 869.7217) 
(list 3840.135 869.7319) 
(list 3840.135 869.7422) 
(list 3840.135 869.7525) 
(list 3840.135 869.7628) 
(list 3840.135 869.7731) 
(list 3840.135 869.7833) 
(list 3840.135 869.7936) 
(list 3840.135 869.8039) 
(list 3840.135 869.8142) 
(list 3840.135 869.8244) 
(list 3840.135 869.8347) 
(list 3840.135 869.845) 
(list 3840.135 869.8553) 
(list 3840.135 869.8656) 
(list 3840.135 869.8758) 
(list 3840.135 869.8861) 
(list 3840.135 869.8964) 
(list 3840.135 869.9067) 
(list 3840.135 869.9169) 
(list 3840.135 869.9272) 
(list 3840.135 869.9375) 
(list 3840.135 869.9478) 
(list 3840.135 869.9581) 
(list 3840.135 869.9683) 
(list 3840.135 869.9786) 
(list 3840.135 869.9889) 
(list 3840.135 869.9992) 
(list 3840.135 870.0094) 
(list 3840.135 870.0197) 
(list 3840.135 870.03) 
(list 3840 870.03)))
(apply 'command (append '("pline") coords '("c")))
(setq tap12 (ssadd (entlast) tap12))
(command "_mirror" (entlast) "" "3840,900" "3840,901" "No")
(setq tap12 (ssadd (entlast) tap12))
(setq coords (list 
(list 3840.5059 869.66) 
(list 3840.4958 869.66) 
(list 3840.495 869.6703) 
(list 3840.492 869.6806) 
(list 3840.4869 869.6908) 
(list 3840.4798 869.7011) 
(list 3840.4709 869.7114) 
(list 3840.4606 869.7217) 
(list 3840.4491 869.7319) 
(list 3840.4367 869.7422) 
(list 3840.4238 869.7525) 
(list 3840.4108 869.7628) 
(list 3840.3982 869.7731) 
(list 3840.3863 869.7833) 
(list 3840.3754 869.7936) 
(list 3840.3659 869.8039) 
(list 3840.3581 869.8142) 
(list 3840.3523 869.8244) 
(list 3840.3487 869.8347) 
(list 3840.3473 869.845) 
(list 3840.3482 869.8553) 
(list 3840.3515 869.8656) 
(list 3840.357 869.8758) 
(list 3840.3646 869.8861) 
(list 3840.3741 869.8964) 
(list 3840.3851 869.9067) 
(list 3840.3974 869.9169) 
(list 3840.4106 869.9272) 
(list 3840.4243 869.9375) 
(list 3840.4381 869.9478) 
(list 3840.4516 869.9581) 
(list 3840.4643 869.9683) 
(list 3840.4759 869.9786) 
(list 3840.486 869.9889) 
(list 3840.4943 869.9992) 
(list 3840.5005 870.0094) 
(list 3840.5044 870.0197) 
(list 3840.5059 870.03) 
(list 3840.5059 870.03)))
(apply 'command (append '("pline") coords '("c")))
(setq tap12 (ssadd (entlast) tap12))
(command "_mirror" (entlast) "" "3840,900" "3840,901" "No")
(setq tap12 (ssadd (entlast) tap12))
(setq coords (list 
(list 3841.133 869.66) 
(list 3840.5059 869.66) 
(list 3840.5059 869.6703) 
(list 3840.5059 869.6806) 
(list 3840.5059 869.6908) 
(list 3840.5059 869.7011) 
(list 3840.5059 869.7114) 
(list 3840.5059 869.7217) 
(list 3840.5059 869.7319) 
(list 3840.5059 869.7422) 
(list 3840.5059 869.7525) 
(list 3840.5059 869.7628) 
(list 3840.5059 869.7731) 
(list 3840.5059 869.7833) 
(list 3840.5059 869.7936) 
(list 3840.5059 869.8039) 
(list 3840.5059 869.8142) 
(list 3840.5059 869.8244) 
(list 3840.5059 869.8347) 
(list 3840.5059 869.845) 
(list 3840.5059 869.8553) 
(list 3840.5059 869.8656) 
(list 3840.5059 869.8758) 
(list 3840.5059 869.8861) 
(list 3840.5059 869.8964) 
(list 3840.5059 869.9067) 
(list 3840.5059 869.9169) 
(list 3840.5059 869.9272) 
(list 3840.5059 869.9375) 
(list 3840.5059 869.9478) 
(list 3840.5059 869.9581) 
(list 3840.5059 869.9683) 
(list 3840.5059 869.9786) 
(list 3840.5059 869.9889) 
(list 3840.5059 869.9992) 
(list 3840.5059 870.0094) 
(list 3840.5059 870.0197) 
(list 3840.5059 870.03) 
(list 3841.133 870.03)))
(apply 'command (append '("pline") coords '("c")))
(setq tap12 (ssadd (entlast) tap12))
(command "_mirror" (entlast) "" "3840,900" "3840,901" "No")
(setq tap12 (ssadd (entlast) tap12))
(setq coords (list 
(list 3840 870.03) 
(list 3840.135 870.03) 
(list 3840.135 870.0403) 
(list 3840.135 870.0506) 
(list 3840.135 870.0608) 
(list 3840.135 870.0711) 
(list 3840.135 870.0814) 
(list 3840.135 870.0917) 
(list 3840.135 870.1019) 
(list 3840.135 870.1122) 
(list 3840.135 870.1225) 
(list 3840.135 870.1328) 
(list 3840.135 870.1431) 
(list 3840.135 870.1533) 
(list 3840.135 870.1636) 
(list 3840.135 870.1739) 
(list 3840.135 870.1842) 
(list 3840.135 870.1944) 
(list 3840.135 870.2047) 
(list 3840.135 870.215) 
(list 3840.135 870.2253) 
(list 3840.135 870.2356) 
(list 3840.135 870.2458) 
(list 3840.135 870.2561) 
(list 3840.135 870.2664) 
(list 3840.135 870.2767) 
(list 3840.135 870.2869) 
(list 3840.135 870.2972) 
(list 3840.135 870.3075) 
(list 3840.135 870.3178) 
(list 3840.135 870.3281) 
(list 3840.135 870.3383) 
(list 3840.135 870.3486) 
(list 3840.135 870.3589) 
(list 3840.135 870.3692) 
(list 3840.135 870.3794) 
(list 3840.135 870.3897) 
(list 3840.135 870.4) 
(list 3840 870.4)))
(apply 'command (append '("pline") coords '("c")))
(setq tap12 (ssadd (entlast) tap12))
(command "_mirror" (entlast) "" "3840,900" "3840,901" "No")
(setq tap12 (ssadd (entlast) tap12))
(setq coords (list 
(list 3840.516 870.03) 
(list 3840.5059 870.03) 
(list 3840.5049 870.0403) 
(list 3840.5015 870.0506) 
(list 3840.4957 870.0608) 
(list 3840.4878 870.0711) 
(list 3840.4778 870.0814) 
(list 3840.4662 870.0917) 
(list 3840.4532 870.1019) 
(list 3840.4393 870.1122) 
(list 3840.4249 870.1225) 
(list 3840.4103 870.1328) 
(list 3840.3962 870.1431) 
(list 3840.3828 870.1533) 
(list 3840.3706 870.1636) 
(list 3840.36 870.1739) 
(list 3840.3514 870.1842) 
(list 3840.3449 870.1944) 
(list 3840.3408 870.2047) 
(list 3840.3393 870.215) 
(list 3840.3404 870.2253) 
(list 3840.3441 870.2356) 
(list 3840.3503 870.2458) 
(list 3840.3587 870.2561) 
(list 3840.3693 870.2664) 
(list 3840.3816 870.2767) 
(list 3840.3954 870.2869) 
(list 3840.4101 870.2972) 
(list 3840.4254 870.3075) 
(list 3840.4408 870.3178) 
(list 3840.4558 870.3281) 
(list 3840.4699 870.3383) 
(list 3840.4828 870.3486) 
(list 3840.494 870.3589) 
(list 3840.5032 870.3692) 
(list 3840.51 870.3794) 
(list 3840.5144 870.3897) 
(list 3840.516 870.4) 
(list 3840.516 870.4)))
(apply 'command (append '("pline") coords '("c")))
(setq tap12 (ssadd (entlast) tap12))
(command "_mirror" (entlast) "" "3840,900" "3840,901" "No")
(setq tap12 (ssadd (entlast) tap12))
(setq coords (list 
(list 3841.133 870.03) 
(list 3840.516 870.03) 
(list 3840.516 870.0403) 
(list 3840.516 870.0506) 
(list 3840.516 870.0608) 
(list 3840.516 870.0711) 
(list 3840.516 870.0814) 
(list 3840.516 870.0917) 
(list 3840.516 870.1019) 
(list 3840.516 870.1122) 
(list 3840.516 870.1225) 
(list 3840.516 870.1328) 
(list 3840.516 870.1431) 
(list 3840.516 870.1533) 
(list 3840.516 870.1636) 
(list 3840.516 870.1739) 
(list 3840.516 870.1842) 
(list 3840.516 870.1944) 
(list 3840.516 870.2047) 
(list 3840.516 870.215) 
(list 3840.516 870.2253) 
(list 3840.516 870.2356) 
(list 3840.516 870.2458) 
(list 3840.516 870.2561) 
(list 3840.516 870.2664) 
(list 3840.516 870.2767) 
(list 3840.516 870.2869) 
(list 3840.516 870.2972) 
(list 3840.516 870.3075) 
(list 3840.516 870.3178) 
(list 3840.516 870.3281) 
(list 3840.516 870.3383) 
(list 3840.516 870.3486) 
(list 3840.516 870.3589) 
(list 3840.516 870.3692) 
(list 3840.516 870.3794) 
(list 3840.516 870.3897) 
(list 3840.516 870.4) 
(list 3841.133 870.4)))
(apply 'command (append '("pline") coords '("c")))
(setq tap12 (ssadd (entlast) tap12))
(command "_mirror" (entlast) "" "3840,900" "3840,901" "No")
(setq tap12 (ssadd (entlast) tap12))
(setq coords (list 
(list 3840 870.4) 
(list 3840.135 870.4) 
(list 3840.135 870.4103) 
(list 3840.135 870.4206) 
(list 3840.135 870.4308) 
(list 3840.135 870.4411) 
(list 3840.135 870.4514) 
(list 3840.135 870.4617) 
(list 3840.135 870.4719) 
(list 3840.135 870.4822) 
(list 3840.135 870.4925) 
(list 3840.135 870.5028) 
(list 3840.135 870.5131) 
(list 3840.135 870.5233) 
(list 3840.135 870.5336) 
(list 3840.135 870.5439) 
(list 3840.135 870.5542) 
(list 3840.135 870.5644) 
(list 3840.135 870.5747) 
(list 3840.135 870.585) 
(list 3840.135 870.5953) 
(list 3840.135 870.6056) 
(list 3840.135 870.6158) 
(list 3840.135 870.6261) 
(list 3840.135 870.6364) 
(list 3840.135 870.6467) 
(list 3840.135 870.6569) 
(list 3840.135 870.6672) 
(list 3840.135 870.6775) 
(list 3840.135 870.6878) 
(list 3840.135 870.6981) 
(list 3840.135 870.7083) 
(list 3840.135 870.7186) 
(list 3840.135 870.7289) 
(list 3840.135 870.7392) 
(list 3840.135 870.7494) 
(list 3840.135 870.7597) 
(list 3840.135 870.77) 
(list 3840 870.77)))
(apply 'command (append '("pline") coords '("c")))
(setq tap12 (ssadd (entlast) tap12))
(command "_mirror" (entlast) "" "3840,900" "3840,901" "No")
(setq tap12 (ssadd (entlast) tap12))
(setq coords (list 
(list 3840.5261 870.4) 
(list 3840.516 870.4) 
(list 3840.5149 870.4103) 
(list 3840.5111 870.4206) 
(list 3840.5046 870.4308) 
(list 3840.4958 870.4411) 
(list 3840.4847 870.4514) 
(list 3840.4718 870.4617) 
(list 3840.4574 870.4719) 
(list 3840.4419 870.4822) 
(list 3840.4259 870.4925) 
(list 3840.4098 870.5028) 
(list 3840.3942 870.5131) 
(list 3840.3794 870.5233) 
(list 3840.3659 870.5336) 
(list 3840.3542 870.5439) 
(list 3840.3446 870.5542) 
(list 3840.3375 870.5644) 
(list 3840.333 870.5747) 
(list 3840.3314 870.585) 
(list 3840.3326 870.5953) 
(list 3840.3367 870.6056) 
(list 3840.3435 870.6158) 
(list 3840.3529 870.6261) 
(list 3840.3646 870.6364) 
(list 3840.3782 870.6467) 
(list 3840.3934 870.6569) 
(list 3840.4096 870.6672) 
(list 3840.4265 870.6775) 
(list 3840.4434 870.6878) 
(list 3840.4599 870.6981) 
(list 3840.4755 870.7083) 
(list 3840.4897 870.7186) 
(list 3840.502 870.7289) 
(list 3840.512 870.7392) 
(list 3840.5196 870.7494) 
(list 3840.5243 870.7597) 
(list 3840.5261 870.77) 
(list 3840.5261 870.77)))
(apply 'command (append '("pline") coords '("c")))
(setq tap12 (ssadd (entlast) tap12))
(command "_mirror" (entlast) "" "3840,900" "3840,901" "No")
(setq tap12 (ssadd (entlast) tap12))
(setq coords (list 
(list 3841.133 870.4) 
(list 3840.5261 870.4) 
(list 3840.5261 870.4103) 
(list 3840.5261 870.4206) 
(list 3840.5261 870.4308) 
(list 3840.5261 870.4411) 
(list 3840.5261 870.4514) 
(list 3840.5261 870.4617) 
(list 3840.5261 870.4719) 
(list 3840.5261 870.4822) 
(list 3840.5261 870.4925) 
(list 3840.5261 870.5028) 
(list 3840.5261 870.5131) 
(list 3840.5261 870.5233) 
(list 3840.5261 870.5336) 
(list 3840.5261 870.5439) 
(list 3840.5261 870.5542) 
(list 3840.5261 870.5644) 
(list 3840.5261 870.5747) 
(list 3840.5261 870.585) 
(list 3840.5261 870.5953) 
(list 3840.5261 870.6056) 
(list 3840.5261 870.6158) 
(list 3840.5261 870.6261) 
(list 3840.5261 870.6364) 
(list 3840.5261 870.6467) 
(list 3840.5261 870.6569) 
(list 3840.5261 870.6672) 
(list 3840.5261 870.6775) 
(list 3840.5261 870.6878) 
(list 3840.5261 870.6981) 
(list 3840.5261 870.7083) 
(list 3840.5261 870.7186) 
(list 3840.5261 870.7289) 
(list 3840.5261 870.7392) 
(list 3840.5261 870.7494) 
(list 3840.5261 870.7597) 
(list 3840.5261 870.77) 
(list 3841.133 870.77)))
(apply 'command (append '("pline") coords '("c")))
(setq tap12 (ssadd (entlast) tap12))
(command "_mirror" (entlast) "" "3840,900" "3840,901" "No")
(setq tap12 (ssadd (entlast) tap12))
(setq coords (list 
(list 3840 870.77) 
(list 3840.135 870.77) 
(list 3840.135 870.7803) 
(list 3840.135 870.7906) 
(list 3840.135 870.8008) 
(list 3840.135 870.8111) 
(list 3840.135 870.8214) 
(list 3840.135 870.8317) 
(list 3840.135 870.8419) 
(list 3840.135 870.8522) 
(list 3840.135 870.8625) 
(list 3840.135 870.8728) 
(list 3840.135 870.8831) 
(list 3840.135 870.8933) 
(list 3840.135 870.9036) 
(list 3840.135 870.9139) 
(list 3840.135 870.9242) 
(list 3840.135 870.9344) 
(list 3840.135 870.9447) 
(list 3840.135 870.955) 
(list 3840.135 870.9653) 
(list 3840.135 870.9756) 
(list 3840.135 870.9858) 
(list 3840.135 870.9961) 
(list 3840.135 871.0064) 
(list 3840.135 871.0167) 
(list 3840.135 871.0269) 
(list 3840.135 871.0372) 
(list 3840.135 871.0475) 
(list 3840.135 871.0578) 
(list 3840.135 871.0681) 
(list 3840.135 871.0783) 
(list 3840.135 871.0886) 
(list 3840.135 871.0989) 
(list 3840.135 871.1092) 
(list 3840.135 871.1194) 
(list 3840.135 871.1297) 
(list 3840.135 871.14) 
(list 3840 871.14)))
(apply 'command (append '("pline") coords '("c")))
(setq tap12 (ssadd (entlast) tap12))
(command "_mirror" (entlast) "" "3840,900" "3840,901" "No")
(setq tap12 (ssadd (entlast) tap12))
(setq coords (list 
(list 3840.5362 870.77) 
(list 3840.5261 870.77) 
(list 3840.5249 870.7803) 
(list 3840.5206 870.7906) 
(list 3840.5135 870.8008) 
(list 3840.5037 870.8111) 
(list 3840.4916 870.8214) 
(list 3840.4773 870.8317) 
(list 3840.4615 870.8419) 
(list 3840.4446 870.8522) 
(list 3840.427 870.8625) 
(list 3840.4093 870.8728) 
(list 3840.3921 870.8831) 
(list 3840.3759 870.8933) 
(list 3840.3612 870.9036) 
(list 3840.3483 870.9139) 
(list 3840.3379 870.9242) 
(list 3840.3301 870.9344) 
(list 3840.3252 870.9447) 
(list 3840.3234 870.955) 
(list 3840.3247 870.9653) 
(list 3840.3292 870.9756) 
(list 3840.3367 870.9858) 
(list 3840.347 870.9961) 
(list 3840.3598 871.0064) 
(list 3840.3748 871.0167) 
(list 3840.3913 871.0269) 
(list 3840.4091 871.0372) 
(list 3840.4275 871.0475) 
(list 3840.446 871.0578) 
(list 3840.4641 871.0681) 
(list 3840.4811 871.0783) 
(list 3840.4965 871.0886) 
(list 3840.51 871.0989) 
(list 3840.5209 871.1092) 
(list 3840.5291 871.1194) 
(list 3840.5343 871.1297) 
(list 3840.5362 871.14) 
(list 3840.5362 871.14)))
(apply 'command (append '("pline") coords '("c")))
(setq tap12 (ssadd (entlast) tap12))
(command "_mirror" (entlast) "" "3840,900" "3840,901" "No")
(setq tap12 (ssadd (entlast) tap12))
(setq coords (list 
(list 3841.133 870.77) 
(list 3840.5362 870.77) 
(list 3840.5362 870.7803) 
(list 3840.5362 870.7906) 
(list 3840.5362 870.8008) 
(list 3840.5362 870.8111) 
(list 3840.5362 870.8214) 
(list 3840.5362 870.8317) 
(list 3840.5362 870.8419) 
(list 3840.5362 870.8522) 
(list 3840.5362 870.8625) 
(list 3840.5362 870.8728) 
(list 3840.5362 870.8831) 
(list 3840.5362 870.8933) 
(list 3840.5362 870.9036) 
(list 3840.5362 870.9139) 
(list 3840.5362 870.9242) 
(list 3840.5362 870.9344) 
(list 3840.5362 870.9447) 
(list 3840.5362 870.955) 
(list 3840.5362 870.9653) 
(list 3840.5362 870.9756) 
(list 3840.5362 870.9858) 
(list 3840.5362 870.9961) 
(list 3840.5362 871.0064) 
(list 3840.5362 871.0167) 
(list 3840.5362 871.0269) 
(list 3840.5362 871.0372) 
(list 3840.5362 871.0475) 
(list 3840.5362 871.0578) 
(list 3840.5362 871.0681) 
(list 3840.5362 871.0783) 
(list 3840.5362 871.0886) 
(list 3840.5362 871.0989) 
(list 3840.5362 871.1092) 
(list 3840.5362 871.1194) 
(list 3840.5362 871.1297) 
(list 3840.5362 871.14) 
(list 3841.133 871.14)))
(apply 'command (append '("pline") coords '("c")))
(setq tap12 (ssadd (entlast) tap12))
(command "_mirror" (entlast) "" "3840,900" "3840,901" "No")
(setq tap12 (ssadd (entlast) tap12))
(setq coords (list 
(list 3840 871.14) 
(list 3840.135 871.14) 
(list 3840.135 871.1503) 
(list 3840.135 871.1606) 
(list 3840.135 871.1708) 
(list 3840.135 871.1811) 
(list 3840.135 871.1914) 
(list 3840.135 871.2017) 
(list 3840.135 871.2119) 
(list 3840.135 871.2222) 
(list 3840.135 871.2325) 
(list 3840.135 871.2428) 
(list 3840.135 871.2531) 
(list 3840.135 871.2633) 
(list 3840.135 871.2736) 
(list 3840.135 871.2839) 
(list 3840.135 871.2942) 
(list 3840.135 871.3044) 
(list 3840.135 871.3147) 
(list 3840.135 871.325) 
(list 3840.135 871.3353) 
(list 3840.135 871.3456) 
(list 3840.135 871.3558) 
(list 3840.135 871.3661) 
(list 3840.135 871.3764) 
(list 3840.135 871.3867) 
(list 3840.135 871.3969) 
(list 3840.135 871.4072) 
(list 3840.135 871.4175) 
(list 3840.135 871.4278) 
(list 3840.135 871.4381) 
(list 3840.135 871.4483) 
(list 3840.135 871.4586) 
(list 3840.135 871.4689) 
(list 3840.135 871.4792) 
(list 3840.135 871.4894) 
(list 3840.135 871.4997) 
(list 3840.135 871.51) 
(list 3840 871.51)))
(apply 'command (append '("pline") coords '("c")))
(setq tap12 (ssadd (entlast) tap12))
(command "_mirror" (entlast) "" "3840,900" "3840,901" "No")
(setq tap12 (ssadd (entlast) tap12))
(setq coords (list 
(list 3840.5463 871.14) 
(list 3840.5362 871.14) 
(list 3840.5348 871.1503) 
(list 3840.5302 871.1606) 
(list 3840.5224 871.1708) 
(list 3840.5117 871.1811) 
(list 3840.4984 871.1914) 
(list 3840.4829 871.2017) 
(list 3840.4657 871.2119) 
(list 3840.4472 871.2222) 
(list 3840.4281 871.2325) 
(list 3840.4088 871.2428) 
(list 3840.3901 871.2531) 
(list 3840.3725 871.2633) 
(list 3840.3564 871.2736) 
(list 3840.3425 871.2839) 
(list 3840.3311 871.2942) 
(list 3840.3226 871.3044) 
(list 3840.3173 871.3147) 
(list 3840.3154 871.325) 
(list 3840.3169 871.3353) 
(list 3840.3218 871.3456) 
(list 3840.33 871.3558) 
(list 3840.3412 871.3661) 
(list 3840.3551 871.3764) 
(list 3840.3713 871.3867) 
(list 3840.3893 871.3969) 
(list 3840.4086 871.4072) 
(list 3840.4286 871.4175) 
(list 3840.4487 871.4278) 
(list 3840.4682 871.4381) 
(list 3840.4867 871.4483) 
(list 3840.5034 871.4586) 
(list 3840.5179 871.4689) 
(list 3840.5298 871.4792) 
(list 3840.5387 871.4894) 
(list 3840.5442 871.4997) 
(list 3840.5463 871.51) 
(list 3840.5463 871.51)))
(apply 'command (append '("pline") coords '("c")))
(setq tap12 (ssadd (entlast) tap12))
(command "_mirror" (entlast) "" "3840,900" "3840,901" "No")
(setq tap12 (ssadd (entlast) tap12))
(setq coords (list 
(list 3841.133 871.14) 
(list 3840.5463 871.14) 
(list 3840.5463 871.1503) 
(list 3840.5463 871.1606) 
(list 3840.5463 871.1708) 
(list 3840.5463 871.1811) 
(list 3840.5463 871.1914) 
(list 3840.5463 871.2017) 
(list 3840.5463 871.2119) 
(list 3840.5463 871.2222) 
(list 3840.5463 871.2325) 
(list 3840.5463 871.2428) 
(list 3840.5463 871.2531) 
(list 3840.5463 871.2633) 
(list 3840.5463 871.2736) 
(list 3840.5463 871.2839) 
(list 3840.5463 871.2942) 
(list 3840.5463 871.3044) 
(list 3840.5463 871.3147) 
(list 3840.5463 871.325) 
(list 3840.5463 871.3353) 
(list 3840.5463 871.3456) 
(list 3840.5463 871.3558) 
(list 3840.5463 871.3661) 
(list 3840.5463 871.3764) 
(list 3840.5463 871.3867) 
(list 3840.5463 871.3969) 
(list 3840.5463 871.4072) 
(list 3840.5463 871.4175) 
(list 3840.5463 871.4278) 
(list 3840.5463 871.4381) 
(list 3840.5463 871.4483) 
(list 3840.5463 871.4586) 
(list 3840.5463 871.4689) 
(list 3840.5463 871.4792) 
(list 3840.5463 871.4894) 
(list 3840.5463 871.4997) 
(list 3840.5463 871.51) 
(list 3841.133 871.51)))
(apply 'command (append '("pline") coords '("c")))
(setq tap12 (ssadd (entlast) tap12))
(command "_mirror" (entlast) "" "3840,900" "3840,901" "No")
(setq tap12 (ssadd (entlast) tap12))
(setq coords (list 
(list 3840 871.51) 
(list 3840.135 871.51) 
(list 3840.135 871.5203) 
(list 3840.135 871.5306) 
(list 3840.135 871.5408) 
(list 3840.135 871.5511) 
(list 3840.135 871.5614) 
(list 3840.135 871.5717) 
(list 3840.135 871.5819) 
(list 3840.135 871.5922) 
(list 3840.135 871.6025) 
(list 3840.135 871.6128) 
(list 3840.135 871.6231) 
(list 3840.135 871.6333) 
(list 3840.135 871.6436) 
(list 3840.135 871.6539) 
(list 3840.135 871.6642) 
(list 3840.135 871.6744) 
(list 3840.135 871.6847) 
(list 3840.135 871.695) 
(list 3840.135 871.7053) 
(list 3840.135 871.7156) 
(list 3840.135 871.7258) 
(list 3840.135 871.7361) 
(list 3840.135 871.7464) 
(list 3840.135 871.7567) 
(list 3840.135 871.7669) 
(list 3840.135 871.7772) 
(list 3840.135 871.7875) 
(list 3840.135 871.7978) 
(list 3840.135 871.8081) 
(list 3840.135 871.8183) 
(list 3840.135 871.8286) 
(list 3840.135 871.8389) 
(list 3840.135 871.8492) 
(list 3840.135 871.8594) 
(list 3840.135 871.8697) 
(list 3840.135 871.88) 
(list 3840 871.88)))
(apply 'command (append '("pline") coords '("c")))
(setq tap12 (ssadd (entlast) tap12))
(command "_mirror" (entlast) "" "3840,900" "3840,901" "No")
(setq tap12 (ssadd (entlast) tap12))
(setq coords (list 
(list 3840.5564 871.51) 
(list 3840.5463 871.51) 
(list 3840.5448 871.5203) 
(list 3840.5397 871.5306) 
(list 3840.5313 871.5408) 
(list 3840.5197 871.5511) 
(list 3840.5053 871.5614) 
(list 3840.4885 871.5717) 
(list 3840.4698 871.5819) 
(list 3840.4498 871.5922) 
(list 3840.4291 871.6025) 
(list 3840.4083 871.6128) 
(list 3840.3881 871.6231) 
(list 3840.369 871.6333) 
(list 3840.3517 871.6436) 
(list 3840.3366 871.6539) 
(list 3840.3244 871.6642) 
(list 3840.3152 871.6744) 
(list 3840.3095 871.6847) 
(list 3840.3075 871.695) 
(list 3840.3091 871.7053) 
(list 3840.3144 871.7156) 
(list 3840.3232 871.7258) 
(list 3840.3353 871.7361) 
(list 3840.3504 871.7464) 
(list 3840.3679 871.7567) 
(list 3840.3873 871.7669) 
(list 3840.4081 871.7772) 
(list 3840.4297 871.7875) 
(list 3840.4513 871.7978) 
(list 3840.4724 871.8081) 
(list 3840.4922 871.8183) 
(list 3840.5103 871.8286) 
(list 3840.5259 871.8389) 
(list 3840.5387 871.8492) 
(list 3840.5482 871.8594) 
(list 3840.5542 871.8697) 
(list 3840.5564 871.88) 
(list 3840.5564 871.88)))
(apply 'command (append '("pline") coords '("c")))
(setq tap12 (ssadd (entlast) tap12))
(command "_mirror" (entlast) "" "3840,900" "3840,901" "No")
(setq tap12 (ssadd (entlast) tap12))
(setq coords (list 
(list 3841.133 871.51) 
(list 3840.5564 871.51) 
(list 3840.5564 871.5203) 
(list 3840.5564 871.5306) 
(list 3840.5564 871.5408) 
(list 3840.5564 871.5511) 
(list 3840.5564 871.5614) 
(list 3840.5564 871.5717) 
(list 3840.5564 871.5819) 
(list 3840.5564 871.5922) 
(list 3840.5564 871.6025) 
(list 3840.5564 871.6128) 
(list 3840.5564 871.6231) 
(list 3840.5564 871.6333) 
(list 3840.5564 871.6436) 
(list 3840.5564 871.6539) 
(list 3840.5564 871.6642) 
(list 3840.5564 871.6744) 
(list 3840.5564 871.6847) 
(list 3840.5564 871.695) 
(list 3840.5564 871.7053) 
(list 3840.5564 871.7156) 
(list 3840.5564 871.7258) 
(list 3840.5564 871.7361) 
(list 3840.5564 871.7464) 
(list 3840.5564 871.7567) 
(list 3840.5564 871.7669) 
(list 3840.5564 871.7772) 
(list 3840.5564 871.7875) 
(list 3840.5564 871.7978) 
(list 3840.5564 871.8081) 
(list 3840.5564 871.8183) 
(list 3840.5564 871.8286) 
(list 3840.5564 871.8389) 
(list 3840.5564 871.8492) 
(list 3840.5564 871.8594) 
(list 3840.5564 871.8697) 
(list 3840.5564 871.88) 
(list 3841.133 871.88)))
(apply 'command (append '("pline") coords '("c")))
(setq tap12 (ssadd (entlast) tap12))
(command "_mirror" (entlast) "" "3840,900" "3840,901" "No")
(setq tap12 (ssadd (entlast) tap12))
(setq coords (list 
(list 3840 871.88) 
(list 3840.135 871.88) 
(list 3840.135 871.8903) 
(list 3840.135 871.9006) 
(list 3840.135 871.9108) 
(list 3840.135 871.9211) 
(list 3840.135 871.9314) 
(list 3840.135 871.9417) 
(list 3840.135 871.9519) 
(list 3840.135 871.9622) 
(list 3840.135 871.9725) 
(list 3840.135 871.9828) 
(list 3840.135 871.9931) 
(list 3840.135 872.0033) 
(list 3840.135 872.0136) 
(list 3840.135 872.0239) 
(list 3840.135 872.0342) 
(list 3840.135 872.0444) 
(list 3840.135 872.0547) 
(list 3840.135 872.065) 
(list 3840.135 872.0753) 
(list 3840.135 872.0856) 
(list 3840.135 872.0958) 
(list 3840.135 872.1061) 
(list 3840.135 872.1164) 
(list 3840.135 872.1267) 
(list 3840.135 872.1369) 
(list 3840.135 872.1472) 
(list 3840.135 872.1575) 
(list 3840.135 872.1678) 
(list 3840.135 872.1781) 
(list 3840.135 872.1883) 
(list 3840.135 872.1986) 
(list 3840.135 872.2089) 
(list 3840.135 872.2192) 
(list 3840.135 872.2294) 
(list 3840.135 872.2397) 
(list 3840.135 872.25) 
(list 3840 872.25)))
(apply 'command (append '("pline") coords '("c")))
(setq tap12 (ssadd (entlast) tap12))
(command "_mirror" (entlast) "" "3840,900" "3840,901" "No")
(setq tap12 (ssadd (entlast) tap12))
(setq coords (list 
(list 3840.5665 871.88) 
(list 3840.5564 871.88) 
(list 3840.5548 871.8903) 
(list 3840.5493 871.9006) 
(list 3840.5402 871.9108) 
(list 3840.5277 871.9211) 
(list 3840.5122 871.9314) 
(list 3840.4941 871.9417) 
(list 3840.474 871.9519) 
(list 3840.4525 871.9622) 
(list 3840.4302 871.9725) 
(list 3840.4078 871.9828) 
(list 3840.3861 871.9931) 
(list 3840.3656 872.0033) 
(list 3840.3469 872.0136) 
(list 3840.3308 872.0239) 
(list 3840.3176 872.0342) 
(list 3840.3078 872.0444) 
(list 3840.3017 872.0547) 
(list 3840.2995 872.065) 
(list 3840.3013 872.0753) 
(list 3840.307 872.0856) 
(list 3840.3165 872.0958) 
(list 3840.3295 872.1061) 
(list 3840.3456 872.1164) 
(list 3840.3644 872.1267) 
(list 3840.3853 872.1369) 
(list 3840.4076 872.1472) 
(list 3840.4307 872.1575) 
(list 3840.4539 872.1678) 
(list 3840.4765 872.1781) 
(list 3840.4978 872.1883) 
(list 3840.5171 872.1986) 
(list 3840.5339 872.2089) 
(list 3840.5476 872.2192) 
(list 3840.5578 872.2294) 
(list 3840.5642 872.2397) 
(list 3840.5665 872.25) 
(list 3840.5665 872.25)))
(apply 'command (append '("pline") coords '("c")))
(setq tap12 (ssadd (entlast) tap12))
(command "_mirror" (entlast) "" "3840,900" "3840,901" "No")
(setq tap12 (ssadd (entlast) tap12))
(setq coords (list 
(list 3841.133 871.88) 
(list 3840.5665 871.88) 
(list 3840.5665 871.8903) 
(list 3840.5665 871.9006) 
(list 3840.5665 871.9108) 
(list 3840.5665 871.9211) 
(list 3840.5665 871.9314) 
(list 3840.5665 871.9417) 
(list 3840.5665 871.9519) 
(list 3840.5665 871.9622) 
(list 3840.5665 871.9725) 
(list 3840.5665 871.9828) 
(list 3840.5665 871.9931) 
(list 3840.5665 872.0033) 
(list 3840.5665 872.0136) 
(list 3840.5665 872.0239) 
(list 3840.5665 872.0342) 
(list 3840.5665 872.0444) 
(list 3840.5665 872.0547) 
(list 3840.5665 872.065) 
(list 3840.5665 872.0753) 
(list 3840.5665 872.0856) 
(list 3840.5665 872.0958) 
(list 3840.5665 872.1061) 
(list 3840.5665 872.1164) 
(list 3840.5665 872.1267) 
(list 3840.5665 872.1369) 
(list 3840.5665 872.1472) 
(list 3840.5665 872.1575) 
(list 3840.5665 872.1678) 
(list 3840.5665 872.1781) 
(list 3840.5665 872.1883) 
(list 3840.5665 872.1986) 
(list 3840.5665 872.2089) 
(list 3840.5665 872.2192) 
(list 3840.5665 872.2294) 
(list 3840.5665 872.2397) 
(list 3840.5665 872.25) 
(list 3841.133 872.25)))
(apply 'command (append '("pline") coords '("c")))
(setq tap12 (ssadd (entlast) tap12))
(command "_mirror" (entlast) "" "3840,900" "3840,901" "No")
(setq tap12 (ssadd (entlast) tap12))
(command "_block" "blktap12" "3840,900" tap12 "")
(command "_insert" "blktap12" "3840,900" "1" "1" "0")
(command "_insert" "blktap12" "3840,900" "1" "1" "180")
(setq uc12 nil)
(setq uc12 (ssadd))
(setq coords (list 
(list 0 -0.185) 
(list 0.135 -0.185) 
(list 0.135 -0.17472) 
(list 0.135 -0.16444) 
(list 0.135 -0.15417) 
(list 0.135 -0.14389) 
(list 0.135 -0.13361) 
(list 0.135 -0.12333) 
(list 0.135 -0.11306) 
(list 0.135 -0.10278) 
(list 0.135 -0.0925) 
(list 0.135 -0.082222) 
(list 0.135 -0.071944) 
(list 0.135 -0.061667) 
(list 0.135 -0.051389) 
(list 0.135 -0.041111) 
(list 0.135 -0.030833) 
(list 0.135 -0.020556) 
(list 0.135 -0.010278) 
(list 0.135 0) 
(list 0.135 0.010278) 
(list 0.135 0.020556) 
(list 0.135 0.030833) 
(list 0.135 0.041111) 
(list 0.135 0.051389) 
(list 0.135 0.061667) 
(list 0.135 0.071944) 
(list 0.135 0.082222) 
(list 0.135 0.0925) 
(list 0.135 0.10278) 
(list 0.135 0.11306) 
(list 0.135 0.12333) 
(list 0.135 0.13361) 
(list 0.135 0.14389) 
(list 0.135 0.15417) 
(list 0.135 0.16444) 
(list 0.135 0.17472) 
(list 0.135 0.185) 
(list 0 0.185)))
(apply 'command (append '("pline") coords '("c")))
(setq uc12 (ssadd (entlast) uc12))
(setq coords (list 
(list 1.133 -0.185) 
(list 0.5665 -0.185) 
(list 0.56444 -0.17472) 
(list 0.55833 -0.16444) 
(list 0.54835 -0.15417) 
(list 0.5348 -0.14389) 
(list 0.5181 -0.13361) 
(list 0.49875 -0.12333) 
(list 0.47734 -0.11306) 
(list 0.45453 -0.10278) 
(list 0.431 -0.0925) 
(list 0.40747 -0.082222) 
(list 0.38466 -0.071944) 
(list 0.36325 -0.061667) 
(list 0.3439 -0.051389) 
(list 0.3272 -0.041111) 
(list 0.31365 -0.030833) 
(list 0.30367 -0.020556) 
(list 0.29756 -0.010278) 
(list 0.2955 0) 
(list 0.29756 0.010278) 
(list 0.30367 0.020556) 
(list 0.31365 0.030833) 
(list 0.3272 0.041111) 
(list 0.3439 0.051389) 
(list 0.36325 0.061667) 
(list 0.38466 0.071944) 
(list 0.40747 0.082222) 
(list 0.431 0.0925) 
(list 0.45453 0.10278) 
(list 0.47734 0.11306) 
(list 0.49875 0.12333) 
(list 0.5181 0.13361) 
(list 0.5348 0.14389) 
(list 0.54835 0.15417) 
(list 0.55833 0.16444) 
(list 0.56444 0.17472) 
(list 0.5665 0.185) 
(list 1.133 0.185)))
(apply 'command (append '("pline") coords '("c")))
(setq uc12 (ssadd (entlast) uc12))
(command "_block" "blkuc12" "0,0.185" uc12 "")
(command "_insert" "blkuc12" "3840,872.62" "1" "1" "0")
(command "_insert" "blkuc12" "3840,872.25" "1" "1" "180")
(command "_insert" "blkuc12" "3840,872.99" "1" "1" "0")
(command "_insert" "blkuc12" "3840,872.62" "1" "1" "180")
(command "_insert" "blkuc12" "3840,873.36" "1" "1" "0")
(command "_insert" "blkuc12" "3840,872.99" "1" "1" "180")
(command "_insert" "blkuc12" "3840,873.73" "1" "1" "0")
(command "_insert" "blkuc12" "3840,873.36" "1" "1" "180")
(command "_insert" "blkuc12" "3840,874.1" "1" "1" "0")
(command "_insert" "blkuc12" "3840,873.73" "1" "1" "180")
(command "_insert" "blkuc12" "3840,874.47" "1" "1" "0")
(command "_insert" "blkuc12" "3840,874.1" "1" "1" "180")
(command "_insert" "blkuc12" "3840,874.84" "1" "1" "0")
(command "_insert" "blkuc12" "3840,874.47" "1" "1" "180")
(command "_insert" "blkuc12" "3840,875.21" "1" "1" "0")
(command "_insert" "blkuc12" "3840,874.84" "1" "1" "180")
(command "_insert" "blkuc12" "3840,875.58" "1" "1" "0")
(command "_insert" "blkuc12" "3840,875.21" "1" "1" "180")
(command "_insert" "blkuc12" "3840,875.95" "1" "1" "0")
(command "_insert" "blkuc12" "3840,875.58" "1" "1" "180")
(command "_insert" "blkuc12" "3840,876.32" "1" "1" "0")
(command "_insert" "blkuc12" "3840,875.95" "1" "1" "180")
(command "_insert" "blkuc12" "3840,876.69" "1" "1" "0")
(command "_insert" "blkuc12" "3840,876.32" "1" "1" "180")
(command "_insert" "blkuc12" "3840,877.06" "1" "1" "0")
(command "_insert" "blkuc12" "3840,876.69" "1" "1" "180")
(command "_insert" "blkuc12" "3840,877.43" "1" "1" "0")
(command "_insert" "blkuc12" "3840,877.06" "1" "1" "180")
(command "_insert" "blkuc12" "3840,877.8" "1" "1" "0")
(command "_insert" "blkuc12" "3840,877.43" "1" "1" "180")
(command "_insert" "blkuc12" "3840,878.17" "1" "1" "0")
(command "_insert" "blkuc12" "3840,877.8" "1" "1" "180")
(command "_insert" "blkuc12" "3840,878.54" "1" "1" "0")
(command "_insert" "blkuc12" "3840,878.17" "1" "1" "180")
(command "_insert" "blkuc12" "3840,878.91" "1" "1" "0")
(command "_insert" "blkuc12" "3840,878.54" "1" "1" "180")
(command "_insert" "blkuc12" "3840,879.28" "1" "1" "0")
(command "_insert" "blkuc12" "3840,878.91" "1" "1" "180")
(command "_insert" "blkuc12" "3840,879.65" "1" "1" "0")
(command "_insert" "blkuc12" "3840,879.28" "1" "1" "180")
(command "_insert" "blkuc12" "3840,880.02" "1" "1" "0")
(command "_insert" "blkuc12" "3840,879.65" "1" "1" "180")
(command "_insert" "blkuc12" "3840,880.39" "1" "1" "0")
(command "_insert" "blkuc12" "3840,880.02" "1" "1" "180")
(command "_insert" "blkuc12" "3840,880.76" "1" "1" "0")
(command "_insert" "blkuc12" "3840,880.39" "1" "1" "180")
(command "_insert" "blkuc12" "3840,881.13" "1" "1" "0")
(command "_insert" "blkuc12" "3840,880.76" "1" "1" "180")
(command "_insert" "blkuc12" "3840,881.5" "1" "1" "0")
(command "_insert" "blkuc12" "3840,881.13" "1" "1" "180")
(command "_insert" "blkuc12" "3840,881.87" "1" "1" "0")
(command "_insert" "blkuc12" "3840,881.5" "1" "1" "180")
(command "_insert" "blkuc12" "3840,882.24" "1" "1" "0")
(command "_insert" "blkuc12" "3840,881.87" "1" "1" "180")
(command "_insert" "blkuc12" "3840,882.61" "1" "1" "0")
(command "_insert" "blkuc12" "3840,882.24" "1" "1" "180")
(command "_insert" "blkuc12" "3840,882.98" "1" "1" "0")
(command "_insert" "blkuc12" "3840,882.61" "1" "1" "180")
(command "_insert" "blkuc12" "3840,883.35" "1" "1" "0")
(command "_insert" "blkuc12" "3840,882.98" "1" "1" "180")
(command "_insert" "blkuc12" "3840,883.72" "1" "1" "0")
(command "_insert" "blkuc12" "3840,883.35" "1" "1" "180")
(command "_insert" "blkuc12" "3840,884.09" "1" "1" "0")
(command "_insert" "blkuc12" "3840,883.72" "1" "1" "180")
(command "_insert" "blkuc12" "3840,884.46" "1" "1" "0")
(command "_insert" "blkuc12" "3840,884.09" "1" "1" "180")
(command "_insert" "blkuc12" "3840,884.83" "1" "1" "0")
(command "_insert" "blkuc12" "3840,884.46" "1" "1" "180")
(command "_insert" "blkuc12" "3840,885.2" "1" "1" "0")
(command "_insert" "blkuc12" "3840,884.83" "1" "1" "180")
(command "_insert" "blkuc12" "3840,885.57" "1" "1" "0")
(command "_insert" "blkuc12" "3840,885.2" "1" "1" "180")
(command "_insert" "blkuc12" "3840,885.94" "1" "1" "0")
(command "_insert" "blkuc12" "3840,885.57" "1" "1" "180")
(command "_insert" "blkuc12" "3840,886.31" "1" "1" "0")
(command "_insert" "blkuc12" "3840,885.94" "1" "1" "180")
(command "_insert" "blkuc12" "3840,886.68" "1" "1" "0")
(command "_insert" "blkuc12" "3840,886.31" "1" "1" "180")
(command "_insert" "blkuc12" "3840,887.05" "1" "1" "0")
(command "_insert" "blkuc12" "3840,886.68" "1" "1" "180")
(command "_insert" "blkuc12" "3840,887.42" "1" "1" "0")
(command "_insert" "blkuc12" "3840,887.05" "1" "1" "180")
(command "_insert" "blkuc12" "3840,887.79" "1" "1" "0")
(command "_insert" "blkuc12" "3840,887.42" "1" "1" "180")
(command "_insert" "blkuc12" "3840,888.16" "1" "1" "0")
(command "_insert" "blkuc12" "3840,887.79" "1" "1" "180")
(command "_insert" "blkuc12" "3840,888.53" "1" "1" "0")
(command "_insert" "blkuc12" "3840,888.16" "1" "1" "180")
(command "_insert" "blkuc12" "3840,888.9" "1" "1" "0")
(command "_insert" "blkuc12" "3840,888.53" "1" "1" "180")
(command "_insert" "blkuc12" "3840,889.27" "1" "1" "0")
(command "_insert" "blkuc12" "3840,888.9" "1" "1" "180")
(command "_insert" "blkuc12" "3840,889.64" "1" "1" "0")
(command "_insert" "blkuc12" "3840,889.27" "1" "1" "180")
(command "_insert" "blkuc12" "3840,890.01" "1" "1" "0")
(command "_insert" "blkuc12" "3840,889.64" "1" "1" "180")
(command "_insert" "blkuc12" "3840,890.38" "1" "1" "0")
(command "_insert" "blkuc12" "3840,890.01" "1" "1" "180")
(command "_insert" "blkuc12" "3840,890.75" "1" "1" "0")
(command "_insert" "blkuc12" "3840,890.38" "1" "1" "180")
(command "_insert" "blkuc12" "3840,891.12" "1" "1" "0")
(command "_insert" "blkuc12" "3840,890.75" "1" "1" "180")
(command "_insert" "blkuc12" "3840,891.49" "1" "1" "0")
(command "_insert" "blkuc12" "3840,891.12" "1" "1" "180")
(command "_insert" "blkuc12" "3840,891.86" "1" "1" "0")
(command "_insert" "blkuc12" "3840,891.49" "1" "1" "180")
(command "_insert" "blkuc12" "3840,892.23" "1" "1" "0")
(command "_insert" "blkuc12" "3840,891.86" "1" "1" "180")
(command "_insert" "blkuc12" "3840,892.6" "1" "1" "0")
(command "_insert" "blkuc12" "3840,892.23" "1" "1" "180")
(command "_insert" "blkuc12" "3840,892.97" "1" "1" "0")
(command "_insert" "blkuc12" "3840,892.6" "1" "1" "180")
(command "_insert" "blkuc12" "3840,893.34" "1" "1" "0")
(command "_insert" "blkuc12" "3840,892.97" "1" "1" "180")
(command "_insert" "blkuc12" "3840,893.71" "1" "1" "0")
(command "_insert" "blkuc12" "3840,893.34" "1" "1" "180")
(command "_insert" "blkuc12" "3840,894.08" "1" "1" "0")
(command "_insert" "blkuc12" "3840,893.71" "1" "1" "180")
(command "_insert" "blkuc12" "3840,894.45" "1" "1" "0")
(command "_insert" "blkuc12" "3840,894.08" "1" "1" "180")
(command "_insert" "blkuc12" "3840,894.82" "1" "1" "0")
(command "_insert" "blkuc12" "3840,894.45" "1" "1" "180")
(command "_insert" "blkuc12" "3840,895.19" "1" "1" "0")
(command "_insert" "blkuc12" "3840,894.82" "1" "1" "180")
(command "_insert" "blkuc12" "3840,895.56" "1" "1" "0")
(command "_insert" "blkuc12" "3840,895.19" "1" "1" "180")
(command "_insert" "blkuc12" "3840,895.93" "1" "1" "0")
(command "_insert" "blkuc12" "3840,895.56" "1" "1" "180")
(command "_insert" "blkuc12" "3840,896.3" "1" "1" "0")
(command "_insert" "blkuc12" "3840,895.93" "1" "1" "180")
(command "_insert" "blkuc12" "3840,896.67" "1" "1" "0")
(command "_insert" "blkuc12" "3840,896.3" "1" "1" "180")
(command "_insert" "blkuc12" "3840,897.04" "1" "1" "0")
(command "_insert" "blkuc12" "3840,896.67" "1" "1" "180")
(command "_insert" "blkuc12" "3840,897.41" "1" "1" "0")
(command "_insert" "blkuc12" "3840,897.04" "1" "1" "180")
(command "_insert" "blkuc12" "3840,897.78" "1" "1" "0")
(command "_insert" "blkuc12" "3840,897.41" "1" "1" "180")
(command "_insert" "blkuc12" "3840,898.15" "1" "1" "0")
(command "_insert" "blkuc12" "3840,897.78" "1" "1" "180")
(command "_insert" "blkuc12" "3840,898.52" "1" "1" "0")
(command "_insert" "blkuc12" "3840,898.15" "1" "1" "180")
(command "_insert" "blkuc12" "3840,898.89" "1" "1" "0")
(command "_insert" "blkuc12" "3840,898.52" "1" "1" "180")
(command "_insert" "blkuc12" "3840,899.26" "1" "1" "0")
(command "_insert" "blkuc12" "3840,898.89" "1" "1" "180")
(command "_insert" "blkuc12" "3840,899.63" "1" "1" "0")
(command "_insert" "blkuc12" "3840,899.26" "1" "1" "180")
(command "_insert" "blkuc12" "3840,900" "1" "1" "0")
(command "_insert" "blkuc12" "3840,899.63" "1" "1" "180")
(command "_insert" "blkuc12" "3840,900.37" "1" "1" "0")
(command "_insert" "blkuc12" "3840,900" "1" "1" "180")
(command "_insert" "blkuc12" "3840,900.74" "1" "1" "0")
(command "_insert" "blkuc12" "3840,900.37" "1" "1" "180")
(command "_insert" "blkuc12" "3840,901.11" "1" "1" "0")
(command "_insert" "blkuc12" "3840,900.74" "1" "1" "180")
(command "_insert" "blkuc12" "3840,901.48" "1" "1" "0")
(command "_insert" "blkuc12" "3840,901.11" "1" "1" "180")
(command "_insert" "blkuc12" "3840,901.85" "1" "1" "0")
(command "_insert" "blkuc12" "3840,901.48" "1" "1" "180")
(command "_insert" "blkuc12" "3840,902.22" "1" "1" "0")
(command "_insert" "blkuc12" "3840,901.85" "1" "1" "180")
(command "_insert" "blkuc12" "3840,902.59" "1" "1" "0")
(command "_insert" "blkuc12" "3840,902.22" "1" "1" "180")
(command "_insert" "blkuc12" "3840,902.96" "1" "1" "0")
(command "_insert" "blkuc12" "3840,902.59" "1" "1" "180")
(command "_insert" "blkuc12" "3840,903.33" "1" "1" "0")
(command "_insert" "blkuc12" "3840,902.96" "1" "1" "180")
(command "_insert" "blkuc12" "3840,903.7" "1" "1" "0")
(command "_insert" "blkuc12" "3840,903.33" "1" "1" "180")
(command "_insert" "blkuc12" "3840,904.07" "1" "1" "0")
(command "_insert" "blkuc12" "3840,903.7" "1" "1" "180")
(command "_insert" "blkuc12" "3840,904.44" "1" "1" "0")
(command "_insert" "blkuc12" "3840,904.07" "1" "1" "180")
(command "_insert" "blkuc12" "3840,904.81" "1" "1" "0")
(command "_insert" "blkuc12" "3840,904.44" "1" "1" "180")
(command "_insert" "blkuc12" "3840,905.18" "1" "1" "0")
(command "_insert" "blkuc12" "3840,904.81" "1" "1" "180")
(command "_insert" "blkuc12" "3840,905.55" "1" "1" "0")
(command "_insert" "blkuc12" "3840,905.18" "1" "1" "180")
(command "_insert" "blkuc12" "3840,905.92" "1" "1" "0")
(command "_insert" "blkuc12" "3840,905.55" "1" "1" "180")
(command "_insert" "blkuc12" "3840,906.29" "1" "1" "0")
(command "_insert" "blkuc12" "3840,905.92" "1" "1" "180")
(command "_insert" "blkuc12" "3840,906.66" "1" "1" "0")
(command "_insert" "blkuc12" "3840,906.29" "1" "1" "180")
(command "_insert" "blkuc12" "3840,907.03" "1" "1" "0")
(command "_insert" "blkuc12" "3840,906.66" "1" "1" "180")
(command "_insert" "blkuc12" "3840,907.4" "1" "1" "0")
(command "_insert" "blkuc12" "3840,907.03" "1" "1" "180")
(command "_insert" "blkuc12" "3840,907.77" "1" "1" "0")
(command "_insert" "blkuc12" "3840,907.4" "1" "1" "180")
(command "_insert" "blkuc12" "3840,908.14" "1" "1" "0")
(command "_insert" "blkuc12" "3840,907.77" "1" "1" "180")
(command "_insert" "blkuc12" "3840,908.51" "1" "1" "0")
(command "_insert" "blkuc12" "3840,908.14" "1" "1" "180")
(command "_insert" "blkuc12" "3840,908.88" "1" "1" "0")
(command "_insert" "blkuc12" "3840,908.51" "1" "1" "180")
(command "_insert" "blkuc12" "3840,909.25" "1" "1" "0")
(command "_insert" "blkuc12" "3840,908.88" "1" "1" "180")
(command "_insert" "blkuc12" "3840,909.62" "1" "1" "0")
(command "_insert" "blkuc12" "3840,909.25" "1" "1" "180")
(command "_insert" "blkuc12" "3840,909.99" "1" "1" "0")
(command "_insert" "blkuc12" "3840,909.62" "1" "1" "180")
(command "_insert" "blkuc12" "3840,910.36" "1" "1" "0")
(command "_insert" "blkuc12" "3840,909.99" "1" "1" "180")
(command "_insert" "blkuc12" "3840,910.73" "1" "1" "0")
(command "_insert" "blkuc12" "3840,910.36" "1" "1" "180")
(command "_insert" "blkuc12" "3840,911.1" "1" "1" "0")
(command "_insert" "blkuc12" "3840,910.73" "1" "1" "180")
(command "_insert" "blkuc12" "3840,911.47" "1" "1" "0")
(command "_insert" "blkuc12" "3840,911.1" "1" "1" "180")
(command "_insert" "blkuc12" "3840,911.84" "1" "1" "0")
(command "_insert" "blkuc12" "3840,911.47" "1" "1" "180")
(command "_insert" "blkuc12" "3840,912.21" "1" "1" "0")
(command "_insert" "blkuc12" "3840,911.84" "1" "1" "180")
(command "_insert" "blkuc12" "3840,912.58" "1" "1" "0")
(command "_insert" "blkuc12" "3840,912.21" "1" "1" "180")
(command "_insert" "blkuc12" "3840,912.95" "1" "1" "0")
(command "_insert" "blkuc12" "3840,912.58" "1" "1" "180")
(command "_insert" "blkuc12" "3840,913.32" "1" "1" "0")
(command "_insert" "blkuc12" "3840,912.95" "1" "1" "180")
(command "_insert" "blkuc12" "3840,913.69" "1" "1" "0")
(command "_insert" "blkuc12" "3840,913.32" "1" "1" "180")
(command "_insert" "blkuc12" "3840,914.06" "1" "1" "0")
(command "_insert" "blkuc12" "3840,913.69" "1" "1" "180")
(command "_insert" "blkuc12" "3840,914.43" "1" "1" "0")
(command "_insert" "blkuc12" "3840,914.06" "1" "1" "180")
(command "_insert" "blkuc12" "3840,914.8" "1" "1" "0")
(command "_insert" "blkuc12" "3840,914.43" "1" "1" "180")
(command "_insert" "blkuc12" "3840,915.17" "1" "1" "0")
(command "_insert" "blkuc12" "3840,914.8" "1" "1" "180")
(command "_insert" "blkuc12" "3840,915.54" "1" "1" "0")
(command "_insert" "blkuc12" "3840,915.17" "1" "1" "180")
(command "_insert" "blkuc12" "3840,915.91" "1" "1" "0")
(command "_insert" "blkuc12" "3840,915.54" "1" "1" "180")
(command "_insert" "blkuc12" "3840,916.28" "1" "1" "0")
(command "_insert" "blkuc12" "3840,915.91" "1" "1" "180")
(command "_insert" "blkuc12" "3840,916.65" "1" "1" "0")
(command "_insert" "blkuc12" "3840,916.28" "1" "1" "180")
(command "_insert" "blkuc12" "3840,917.02" "1" "1" "0")
(command "_insert" "blkuc12" "3840,916.65" "1" "1" "180")
(command "_insert" "blkuc12" "3840,917.39" "1" "1" "0")
(command "_insert" "blkuc12" "3840,917.02" "1" "1" "180")
(command "_insert" "blkuc12" "3840,917.76" "1" "1" "0")
(command "_insert" "blkuc12" "3840,917.39" "1" "1" "180")
(command "_insert" "blkuc12" "3840,918.13" "1" "1" "0")
(command "_insert" "blkuc12" "3840,917.76" "1" "1" "180")
(command "_insert" "blkuc12" "3840,918.5" "1" "1" "0")
(command "_insert" "blkuc12" "3840,918.13" "1" "1" "180")
(command "_insert" "blkuc12" "3840,918.87" "1" "1" "0")
(command "_insert" "blkuc12" "3840,918.5" "1" "1" "180")
(command "_insert" "blkuc12" "3840,919.24" "1" "1" "0")
(command "_insert" "blkuc12" "3840,918.87" "1" "1" "180")
(command "_insert" "blkuc12" "3840,919.61" "1" "1" "0")
(command "_insert" "blkuc12" "3840,919.24" "1" "1" "180")
(command "_insert" "blkuc12" "3840,919.98" "1" "1" "0")
(command "_insert" "blkuc12" "3840,919.61" "1" "1" "180")
(command "_insert" "blkuc12" "3840,920.35" "1" "1" "0")
(command "_insert" "blkuc12" "3840,919.98" "1" "1" "180")
(command "_insert" "blkuc12" "3840,920.72" "1" "1" "0")
(command "_insert" "blkuc12" "3840,920.35" "1" "1" "180")
(command "_insert" "blkuc12" "3840,921.09" "1" "1" "0")
(command "_insert" "blkuc12" "3840,920.72" "1" "1" "180")
(command "_insert" "blkuc12" "3840,921.46" "1" "1" "0")
(command "_insert" "blkuc12" "3840,921.09" "1" "1" "180")
(command "_insert" "blkuc12" "3840,921.83" "1" "1" "0")
(command "_insert" "blkuc12" "3840,921.46" "1" "1" "180")
(command "_insert" "blkuc12" "3840,922.2" "1" "1" "0")
(command "_insert" "blkuc12" "3840,921.83" "1" "1" "180")
(command "_insert" "blkuc12" "3840,922.57" "1" "1" "0")
(command "_insert" "blkuc12" "3840,922.2" "1" "1" "180")
(command "_insert" "blkuc12" "3840,922.94" "1" "1" "0")
(command "_insert" "blkuc12" "3840,922.57" "1" "1" "180")
(command "_insert" "blkuc12" "3840,923.31" "1" "1" "0")
(command "_insert" "blkuc12" "3840,922.94" "1" "1" "180")
(command "_insert" "blkuc12" "3840,923.68" "1" "1" "0")
(command "_insert" "blkuc12" "3840,923.31" "1" "1" "180")
(command "_insert" "blkuc12" "3840,924.05" "1" "1" "0")
(command "_insert" "blkuc12" "3840,923.68" "1" "1" "180")
(command "_insert" "blkuc12" "3840,924.42" "1" "1" "0")
(command "_insert" "blkuc12" "3840,924.05" "1" "1" "180")
(command "_insert" "blkuc12" "3840,924.79" "1" "1" "0")
(command "_insert" "blkuc12" "3840,924.42" "1" "1" "180")
(command "_insert" "blkuc12" "3840,925.16" "1" "1" "0")
(command "_insert" "blkuc12" "3840,924.79" "1" "1" "180")
(command "_insert" "blkuc12" "3840,925.53" "1" "1" "0")
(command "_insert" "blkuc12" "3840,925.16" "1" "1" "180")
(command "_insert" "blkuc12" "3840,925.9" "1" "1" "0")
(command "_insert" "blkuc12" "3840,925.53" "1" "1" "180")
(command "_insert" "blkuc12" "3840,926.27" "1" "1" "0")
(command "_insert" "blkuc12" "3840,925.9" "1" "1" "180")
(command "_insert" "blkuc12" "3840,926.64" "1" "1" "0")
(command "_insert" "blkuc12" "3840,926.27" "1" "1" "180")
(command "_insert" "blkuc12" "3840,927.01" "1" "1" "0")
(command "_insert" "blkuc12" "3840,926.64" "1" "1" "180")
(command "_insert" "blkuc12" "3840,927.38" "1" "1" "0")
(command "_insert" "blkuc12" "3840,927.01" "1" "1" "180")
(command "_insert" "blkuc12" "3840,927.75" "1" "1" "0")
(command "_insert" "blkuc12" "3840,927.38" "1" "1" "180")
(command "_layer" "set" "phccover" "")
(command "_rectangle" "3838.867,933.3" "3841.133,866.7")
(command "_layer" "set" "nitride" "")
(setq phc12 currobj)
(command "_layer" "set" "cover" "")
(command "_rectangle" "3838.867,836.7" "3841.133,963.3")
(command "_layer" "set" "nitride" "")
(command "_layer" "set" "text" "")
(command "_circle" "3837.917,846.7" "0.075")
(command "_circle" "3837.542,846.7" "0.15")
(command "_circle" "3837.167,846.7" "0.075")
(command "_circle" "3836.792,846.7" "0.15")
(command "_circle" "3837.917,848.7" "0.075")
(command "_circle" "3837.542,848.7" "0.075")
(command "_circle" "3837.167,848.7" "0.15")
(command "_circle" "3836.792,848.7" "0.15")
(command "_circle" "3837.917,850.7" "0.075")
(command "_circle" "3837.542,850.7" "0.15")
(command "_circle" "3837.167,850.7" "0.15")
(command "_circle" "3836.792,850.7" "0.15")
(command "_circle" "3837.917,852.7" "0.075")
(command "_circle" "3837.542,852.7" "0.075")
(command "_circle" "3837.167,852.7" "0.075")
(command "_circle" "3836.792,852.7" "0.075")
(command "_circle" "3836.417,852.7" "0.15")
(command "_circle" "3837.917,854.7" "0.075")
(command "_circle" "3837.542,854.7" "0.15")
(command "_circle" "3837.167,854.7" "0.075")
(command "_circle" "3836.792,854.7" "0.075")
(command "_circle" "3836.417,854.7" "0.15")
(command "_circle" "3837.917,856.7" "0.075")
(command "_circle" "3837.542,856.7" "0.075")
(command "_circle" "3837.167,856.7" "0.15")
(command "_circle" "3836.792,856.7" "0.075")
(command "_circle" "3836.417,856.7" "0.15")
(command "_circle" "3837.917,858.7" "0.075")
(command "_circle" "3837.542,858.7" "0.15")
(command "_circle" "3837.167,858.7" "0.15")
(command "_circle" "3836.792,858.7" "0.075")
(command "_circle" "3836.417,858.7" "0.15")
(command "_circle" "3837.917,860.7" "0.075")
(command "_circle" "3837.542,860.7" "0.075")
(command "_circle" "3837.167,860.7" "0.075")
(command "_circle" "3836.792,860.7" "0.15")
(command "_circle" "3836.417,860.7" "0.15")
(command "_circle" "3837.917,862.7" "0.075")
(command "_circle" "3837.542,862.7" "0.15")
(command "_circle" "3837.167,862.7" "0.075")
(command "_circle" "3836.792,862.7" "0.15")
(command "_circle" "3836.417,862.7" "0.15")
(command "_circle" "3837.917,864.7" "0.075")
(command "_circle" "3837.542,864.7" "0.075")
(command "_circle" "3837.167,864.7" "0.15")
(command "_circle" "3836.792,864.7" "0.15")
(command "_circle" "3836.417,864.7" "0.15")
(command "_circle" "3837.917,866.7" "0.075")
(command "_circle" "3837.542,866.7" "0.15")
(command "_circle" "3837.167,866.7" "0.15")
(command "_circle" "3836.792,866.7" "0.15")
(command "_circle" "3836.417,866.7" "0.15")
(command "_circle" "3837.917,868.7" "0.075")
(command "_circle" "3837.542,868.7" "0.075")
(command "_circle" "3837.167,868.7" "0.075")
(command "_circle" "3836.792,868.7" "0.075")
(command "_circle" "3836.417,868.7" "0.075")
(command "_circle" "3836.042,868.7" "0.15")
(command "_circle" "3837.917,870.7" "0.075")
(command "_circle" "3837.542,870.7" "0.15")
(command "_circle" "3837.167,870.7" "0.075")
(command "_circle" "3836.792,870.7" "0.075")
(command "_circle" "3836.417,870.7" "0.075")
(command "_circle" "3836.042,870.7" "0.15")
(command "_circle" "3837.917,872.7" "0.075")
(command "_circle" "3837.542,872.7" "0.075")
(command "_circle" "3837.167,872.7" "0.15")
(command "_circle" "3836.792,872.7" "0.075")
(command "_circle" "3836.417,872.7" "0.075")
(command "_circle" "3836.042,872.7" "0.15")
(command "_circle" "3837.917,874.7" "0.075")
(command "_circle" "3837.542,874.7" "0.15")
(command "_circle" "3837.167,874.7" "0.15")
(command "_circle" "3836.792,874.7" "0.075")
(command "_circle" "3836.417,874.7" "0.075")
(command "_circle" "3836.042,874.7" "0.15")
(command "_circle" "3837.917,876.7" "0.075")
(command "_circle" "3837.542,876.7" "0.075")
(command "_circle" "3837.167,876.7" "0.075")
(command "_circle" "3836.792,876.7" "0.15")
(command "_circle" "3836.417,876.7" "0.075")
(command "_circle" "3836.042,876.7" "0.15")
(command "_circle" "3837.917,878.7" "0.075")
(command "_circle" "3837.542,878.7" "0.15")
(command "_circle" "3837.167,878.7" "0.075")
(command "_circle" "3836.792,878.7" "0.15")
(command "_circle" "3836.417,878.7" "0.075")
(command "_circle" "3836.042,878.7" "0.15")
(command "_circle" "3837.917,880.7" "0.075")
(command "_circle" "3837.542,880.7" "0.075")
(command "_circle" "3837.167,880.7" "0.15")
(command "_circle" "3836.792,880.7" "0.15")
(command "_circle" "3836.417,880.7" "0.075")
(command "_circle" "3836.042,880.7" "0.15")
(command "_circle" "3837.917,882.7" "0.075")
(command "_circle" "3837.542,882.7" "0.15")
(command "_circle" "3837.167,882.7" "0.15")
(command "_circle" "3836.792,882.7" "0.15")
(command "_circle" "3836.417,882.7" "0.075")
(command "_circle" "3836.042,882.7" "0.15")
(command "_circle" "3837.917,884.7" "0.075")
(command "_circle" "3837.542,884.7" "0.075")
(command "_circle" "3837.167,884.7" "0.075")
(command "_circle" "3836.792,884.7" "0.075")
(command "_circle" "3836.417,884.7" "0.15")
(command "_circle" "3836.042,884.7" "0.15")
(command "_circle" "3837.917,886.7" "0.075")
(command "_circle" "3837.542,886.7" "0.15")
(command "_circle" "3837.167,886.7" "0.075")
(command "_circle" "3836.792,886.7" "0.075")
(command "_circle" "3836.417,886.7" "0.15")
(command "_circle" "3836.042,886.7" "0.15")
(command "_circle" "3837.917,888.7" "0.075")
(command "_circle" "3837.542,888.7" "0.075")
(command "_circle" "3837.167,888.7" "0.15")
(command "_circle" "3836.792,888.7" "0.075")
(command "_circle" "3836.417,888.7" "0.15")
(command "_circle" "3836.042,888.7" "0.15")
(command "_circle" "3837.917,890.7" "0.075")
(command "_circle" "3837.542,890.7" "0.15")
(command "_circle" "3837.167,890.7" "0.15")
(command "_circle" "3836.792,890.7" "0.075")
(command "_circle" "3836.417,890.7" "0.15")
(command "_circle" "3836.042,890.7" "0.15")
(command "_circle" "3837.917,892.7" "0.075")
(command "_circle" "3837.542,892.7" "0.075")
(command "_circle" "3837.167,892.7" "0.075")
(command "_circle" "3836.792,892.7" "0.15")
(command "_circle" "3836.417,892.7" "0.15")
(command "_circle" "3836.042,892.7" "0.15")
(command "_circle" "3837.917,894.7" "0.075")
(command "_circle" "3837.542,894.7" "0.15")
(command "_circle" "3837.167,894.7" "0.075")
(command "_circle" "3836.792,894.7" "0.15")
(command "_circle" "3836.417,894.7" "0.15")
(command "_circle" "3836.042,894.7" "0.15")
(command "_circle" "3837.917,896.7" "0.075")
(command "_circle" "3837.542,896.7" "0.075")
(command "_circle" "3837.167,896.7" "0.15")
(command "_circle" "3836.792,896.7" "0.15")
(command "_circle" "3836.417,896.7" "0.15")
(command "_circle" "3836.042,896.7" "0.15")
(command "_circle" "3837.917,898.7" "0.075")
(command "_circle" "3837.542,898.7" "0.15")
(command "_circle" "3837.167,898.7" "0.15")
(command "_circle" "3836.792,898.7" "0.15")
(command "_circle" "3836.417,898.7" "0.15")
(command "_circle" "3836.042,898.7" "0.15")
(command "_circle" "3837.917,900.7" "0.075")
(command "_circle" "3837.542,900.7" "0.075")
(command "_circle" "3837.167,900.7" "0.075")
(command "_circle" "3836.792,900.7" "0.075")
(command "_circle" "3836.417,900.7" "0.075")
(command "_circle" "3836.042,900.7" "0.075")
(command "_circle" "3835.667,900.7" "0.15")
(command "_circle" "3837.917,902.7" "0.075")
(command "_circle" "3837.542,902.7" "0.15")
(command "_circle" "3837.167,902.7" "0.075")
(command "_circle" "3836.792,902.7" "0.075")
(command "_circle" "3836.417,902.7" "0.075")
(command "_circle" "3836.042,902.7" "0.075")
(command "_circle" "3835.667,902.7" "0.15")
(command "_circle" "3837.917,904.7" "0.075")
(command "_circle" "3837.542,904.7" "0.075")
(command "_circle" "3837.167,904.7" "0.15")
(command "_circle" "3836.792,904.7" "0.075")
(command "_circle" "3836.417,904.7" "0.075")
(command "_circle" "3836.042,904.7" "0.075")
(command "_circle" "3835.667,904.7" "0.15")
(command "_circle" "3837.917,906.7" "0.075")
(command "_circle" "3837.542,906.7" "0.15")
(command "_circle" "3837.167,906.7" "0.15")
(command "_circle" "3836.792,906.7" "0.075")
(command "_circle" "3836.417,906.7" "0.075")
(command "_circle" "3836.042,906.7" "0.075")
(command "_circle" "3835.667,906.7" "0.15")
(command "_circle" "3837.917,908.7" "0.075")
(command "_circle" "3837.542,908.7" "0.075")
(command "_circle" "3837.167,908.7" "0.075")
(command "_circle" "3836.792,908.7" "0.15")
(command "_circle" "3836.417,908.7" "0.075")
(command "_circle" "3836.042,908.7" "0.075")
(command "_circle" "3835.667,908.7" "0.15")
(command "_circle" "3837.917,910.7" "0.075")
(command "_circle" "3837.542,910.7" "0.15")
(command "_circle" "3837.167,910.7" "0.075")
(command "_circle" "3836.792,910.7" "0.15")
(command "_circle" "3836.417,910.7" "0.075")
(command "_circle" "3836.042,910.7" "0.075")
(command "_circle" "3835.667,910.7" "0.15")
(command "_circle" "3837.917,912.7" "0.075")
(command "_circle" "3837.542,912.7" "0.075")
(command "_circle" "3837.167,912.7" "0.15")
(command "_circle" "3836.792,912.7" "0.15")
(command "_circle" "3836.417,912.7" "0.075")
(command "_circle" "3836.042,912.7" "0.075")
(command "_circle" "3835.667,912.7" "0.15")
(command "_circle" "3837.917,914.7" "0.075")
(command "_circle" "3837.542,914.7" "0.15")
(command "_circle" "3837.167,914.7" "0.15")
(command "_circle" "3836.792,914.7" "0.15")
(command "_circle" "3836.417,914.7" "0.075")
(command "_circle" "3836.042,914.7" "0.075")
(command "_circle" "3835.667,914.7" "0.15")
(command "_circle" "3837.917,916.7" "0.075")
(command "_circle" "3837.542,916.7" "0.075")
(command "_circle" "3837.167,916.7" "0.075")
(command "_circle" "3836.792,916.7" "0.075")
(command "_circle" "3836.417,916.7" "0.15")
(command "_circle" "3836.042,916.7" "0.075")
(command "_circle" "3835.667,916.7" "0.15")
(command "_circle" "3837.917,918.7" "0.075")
(command "_circle" "3837.542,918.7" "0.15")
(command "_circle" "3837.167,918.7" "0.075")
(command "_circle" "3836.792,918.7" "0.075")
(command "_circle" "3836.417,918.7" "0.15")
(command "_circle" "3836.042,918.7" "0.075")
(command "_circle" "3835.667,918.7" "0.15")
(command "_circle" "3837.917,920.7" "0.075")
(command "_circle" "3837.542,920.7" "0.075")
(command "_circle" "3837.167,920.7" "0.15")
(command "_circle" "3836.792,920.7" "0.075")
(command "_circle" "3836.417,920.7" "0.15")
(command "_circle" "3836.042,920.7" "0.075")
(command "_circle" "3835.667,920.7" "0.15")
(command "_circle" "3837.917,922.7" "0.075")
(command "_circle" "3837.542,922.7" "0.15")
(command "_circle" "3837.167,922.7" "0.15")
(command "_circle" "3836.792,922.7" "0.075")
(command "_circle" "3836.417,922.7" "0.15")
(command "_circle" "3836.042,922.7" "0.075")
(command "_circle" "3835.667,922.7" "0.15")
(command "_circle" "3837.917,924.7" "0.075")
(command "_circle" "3837.542,924.7" "0.075")
(command "_circle" "3837.167,924.7" "0.075")
(command "_circle" "3836.792,924.7" "0.15")
(command "_circle" "3836.417,924.7" "0.15")
(command "_circle" "3836.042,924.7" "0.075")
(command "_circle" "3835.667,924.7" "0.15")
(command "_circle" "3837.917,926.7" "0.075")
(command "_circle" "3837.542,926.7" "0.15")
(command "_circle" "3837.167,926.7" "0.075")
(command "_circle" "3836.792,926.7" "0.15")
(command "_circle" "3836.417,926.7" "0.15")
(command "_circle" "3836.042,926.7" "0.075")
(command "_circle" "3835.667,926.7" "0.15")
(command "_circle" "3837.917,928.7" "0.075")
(command "_circle" "3837.542,928.7" "0.075")
(command "_circle" "3837.167,928.7" "0.15")
(command "_circle" "3836.792,928.7" "0.15")
(command "_circle" "3836.417,928.7" "0.15")
(command "_circle" "3836.042,928.7" "0.075")
(command "_circle" "3835.667,928.7" "0.15")
(command "_circle" "3837.917,930.7" "0.075")
(command "_circle" "3837.542,930.7" "0.15")
(command "_circle" "3837.167,930.7" "0.15")
(command "_circle" "3836.792,930.7" "0.15")
(command "_circle" "3836.417,930.7" "0.15")
(command "_circle" "3836.042,930.7" "0.075")
(command "_circle" "3835.667,930.7" "0.15")
(command "_circle" "3837.917,932.7" "0.075")
(command "_circle" "3837.542,932.7" "0.075")
(command "_circle" "3837.167,932.7" "0.075")
(command "_circle" "3836.792,932.7" "0.075")
(command "_circle" "3836.417,932.7" "0.075")
(command "_circle" "3836.042,932.7" "0.15")
(command "_circle" "3835.667,932.7" "0.15")
(command "_circle" "3837.917,934.7" "0.075")
(command "_circle" "3837.542,934.7" "0.15")
(command "_circle" "3837.167,934.7" "0.075")
(command "_circle" "3836.792,934.7" "0.075")
(command "_circle" "3836.417,934.7" "0.075")
(command "_circle" "3836.042,934.7" "0.15")
(command "_circle" "3835.667,934.7" "0.15")
(command "_circle" "3837.917,936.7" "0.075")
(command "_circle" "3837.542,936.7" "0.075")
(command "_circle" "3837.167,936.7" "0.15")
(command "_circle" "3836.792,936.7" "0.075")
(command "_circle" "3836.417,936.7" "0.075")
(command "_circle" "3836.042,936.7" "0.15")
(command "_circle" "3835.667,936.7" "0.15")
(command "_circle" "3837.917,938.7" "0.075")
(command "_circle" "3837.542,938.7" "0.15")
(command "_circle" "3837.167,938.7" "0.15")
(command "_circle" "3836.792,938.7" "0.075")
(command "_circle" "3836.417,938.7" "0.075")
(command "_circle" "3836.042,938.7" "0.15")
(command "_circle" "3835.667,938.7" "0.15")
(command "_circle" "3837.917,940.7" "0.075")
(command "_circle" "3837.542,940.7" "0.075")
(command "_circle" "3837.167,940.7" "0.075")
(command "_circle" "3836.792,940.7" "0.15")
(command "_circle" "3836.417,940.7" "0.075")
(command "_circle" "3836.042,940.7" "0.15")
(command "_circle" "3835.667,940.7" "0.15")
(command "_circle" "3837.917,942.7" "0.075")
(command "_circle" "3837.542,942.7" "0.15")
(command "_circle" "3837.167,942.7" "0.075")
(command "_circle" "3836.792,942.7" "0.15")
(command "_circle" "3836.417,942.7" "0.075")
(command "_circle" "3836.042,942.7" "0.15")
(command "_circle" "3835.667,942.7" "0.15")
(command "_circle" "3837.917,944.7" "0.075")
(command "_circle" "3837.542,944.7" "0.075")
(command "_circle" "3837.167,944.7" "0.15")
(command "_circle" "3836.792,944.7" "0.15")
(command "_circle" "3836.417,944.7" "0.075")
(command "_circle" "3836.042,944.7" "0.15")
(command "_circle" "3835.667,944.7" "0.15")
(command "_circle" "3837.917,946.7" "0.075")
(command "_circle" "3837.542,946.7" "0.15")
(command "_circle" "3837.167,946.7" "0.15")
(command "_circle" "3836.792,946.7" "0.15")
(command "_circle" "3836.417,946.7" "0.075")
(command "_circle" "3836.042,946.7" "0.15")
(command "_circle" "3835.667,946.7" "0.15")
(command "_circle" "3837.917,948.7" "0.075")
(command "_circle" "3837.542,948.7" "0.075")
(command "_circle" "3837.167,948.7" "0.075")
(command "_circle" "3836.792,948.7" "0.075")
(command "_circle" "3836.417,948.7" "0.15")
(command "_circle" "3836.042,948.7" "0.15")
(command "_circle" "3835.667,948.7" "0.15")
(command "_circle" "3837.917,950.7" "0.075")
(command "_circle" "3837.542,950.7" "0.15")
(command "_circle" "3837.167,950.7" "0.075")
(command "_circle" "3836.792,950.7" "0.075")
(command "_circle" "3836.417,950.7" "0.15")
(command "_circle" "3836.042,950.7" "0.15")
(command "_circle" "3835.667,950.7" "0.15")
(command "_circle" "3837.917,952.7" "0.075")
(command "_circle" "3837.542,952.7" "0.075")
(command "_circle" "3837.167,952.7" "0.15")
(command "_circle" "3836.792,952.7" "0.075")
(command "_circle" "3836.417,952.7" "0.15")
(command "_circle" "3836.042,952.7" "0.15")
(command "_circle" "3835.667,952.7" "0.15")
(command "_circle" "3837.917,954.7" "0.075")
(command "_circle" "3837.542,954.7" "0.15")
(command "_circle" "3837.167,954.7" "0.15")
(command "_circle" "3836.792,954.7" "0.075")
(command "_circle" "3836.417,954.7" "0.15")
(command "_circle" "3836.042,954.7" "0.15")
(command "_circle" "3835.667,954.7" "0.15")
(command "_circle" "3837.917,956.7" "0.075")
(command "_circle" "3837.542,956.7" "0.075")
(command "_circle" "3837.167,956.7" "0.075")
(command "_circle" "3836.792,956.7" "0.15")
(command "_circle" "3836.417,956.7" "0.15")
(command "_circle" "3836.042,956.7" "0.15")
(command "_circle" "3835.667,956.7" "0.15")
(command "_circle" "3837.917,958.7" "0.075")
(command "_circle" "3837.542,958.7" "0.15")
(command "_circle" "3837.167,958.7" "0.075")
(command "_circle" "3836.792,958.7" "0.15")
(command "_circle" "3836.417,958.7" "0.15")
(command "_circle" "3836.042,958.7" "0.15")
(command "_circle" "3835.667,958.7" "0.15")
(command "_circle" "3837.917,960.7" "0.075")
(command "_circle" "3837.542,960.7" "0.075")
(command "_circle" "3837.167,960.7" "0.15")
(command "_circle" "3836.792,960.7" "0.15")
(command "_circle" "3836.417,960.7" "0.15")
(command "_circle" "3836.042,960.7" "0.15")
(command "_circle" "3835.667,960.7" "0.15")
(command "_circle" "3837.917,962.7" "0.075")
(command "_circle" "3837.542,962.7" "0.15")
(command "_circle" "3837.167,962.7" "0.15")
(command "_circle" "3836.792,962.7" "0.15")
(command "_circle" "3836.417,962.7" "0.15")
(command "_circle" "3836.042,962.7" "0.15")
(command "_circle" "3835.667,962.7" "0.15")
(command "_layer" "set" "nitride" "")
(command "_layer" "set" "text" "")
(command-s "_text" "3826.867,963.3" "2" "-90" "a = 370 nm" )
(sssetfirst nil (ssget "_L"))
(if (not (numberp (vl-string-search "Mac" (getvar "platform")))) (c:txtexp))
(command "_layer" "set" "nitride" "")
(command "_layer" "set" "text" "")
(command-s "_text" "3823.867,963.3" "2" "-90" "gap = 270 nm" )
(sssetfirst nil (ssget "_L"))
(if (not (numberp (vl-string-search "Mac" (getvar "platform")))) (c:txtexp))
(command "_layer" "set" "nitride" "")
(command "_layer" "set" "text" "")
(command-s "_text" "3820.867,963.3" "2" "-90" "amplitude = 135.5 nm" )
(sssetfirst nil (ssget "_L"))
(if (not (numberp (vl-string-search "Mac" (getvar "platform")))) (c:txtexp))
(command "_layer" "set" "nitride" "")
(command "_layer" "set" "text" "")
(command-s "_text" "3817.867,963.3" "2" "-90" "start width = 280 nm" )
(sssetfirst nil (ssget "_L"))
(if (not (numberp (vl-string-search "Mac" (getvar "platform")))) (c:txtexp))
(command "_layer" "set" "nitride" "")
(command "_layer" "set" "text" "")
(command-s "_text" "3814.867,963.3" "2" "-90" "width = 296 nm" )
(sssetfirst nil (ssget "_L"))
(if (not (numberp (vl-string-search "Mac" (getvar "platform")))) (c:txtexp))
(command "_layer" "set" "nitride" "")
(command "_layer" "set" "text" "")
(command-s "_text" "3811.867,963.3" "2" "-90" "taper: 15" )
(sssetfirst nil (ssget "_L"))
(if (not (numberp (vl-string-search "Mac" (getvar "platform")))) (c:txtexp))
(command "_layer" "set" "nitride" "")
(command "_layer" "set" "text" "")
(command-s "_text" "3808.867,963.3" "2" "-90" "nominal: 150" )
(sssetfirst nil (ssget "_L"))
(if (not (numberp (vl-string-search "Mac" (getvar "platform")))) (c:txtexp))
(command "_layer" "set" "nitride" "")
(command "_layer" "set" "indicators" "")
(setq coords (list 
(list 3760.415 940) 
(list 3760.415 920) 
(list 3740.415 900) 
(list 3760.415 880) 
(list 3760.415 860) 
(list 3760.415 900) 
(list 3760.415 887.0711) 
(list 3747.4861 900) 
(list 3760.415 912.9289) 
(list 3760.415 900)))
(apply 'command (append '("pline") coords '("c")))
(command "._fillet" "radius" "1" "._fillet" "P" (entlast))
(setq coords (list 
(list 3919.585 940) 
(list 3919.585 920) 
(list 3939.585 900) 
(list 3919.585 880) 
(list 3919.585 860) 
(list 3919.585 900) 
(list 3919.585 887.0711) 
(list 3932.5139 900) 
(list 3919.585 912.9289) 
(list 3919.585 900)))
(apply 'command (append '("pline") coords '("c")))
(command "._fillet" "radius" "1" "._fillet" "P" (entlast))
(command "_layer" "set" "holes" "")
(command "_circle" "3758.0629,914.1124" "0.5")
(command "_circle" "3755.7109,911.7603" "0.5")
(command "_circle" "3753.3588,909.4083" "0.5")
(command "_circle" "3751.0067,907.0562" "0.5")
(command "_circle" "3748.6547,904.7041" "0.5")
(command "_circle" "3746.3026,902.3521" "0.5")
(command "_circle" "3743.9505,900" "0.5")
(command "_circle" "3746.3026,897.6479" "0.5")
(command "_circle" "3748.6547,895.2959" "0.5")
(command "_circle" "3751.0067,892.9438" "0.5")
(command "_circle" "3753.3588,890.5917" "0.5")
(command "_circle" "3755.7109,888.2397" "0.5")
(command "_circle" "3758.0629,885.8876" "0.5")
(command "_circle" "3921.9371,914.1124" "0.5")
(command "_circle" "3924.2891,911.7603" "0.5")
(command "_circle" "3926.6412,909.4083" "0.5")
(command "_circle" "3928.9933,907.0562" "0.5")
(command "_circle" "3931.3453,904.7041" "0.5")
(command "_circle" "3933.6974,902.3521" "0.5")
(command "_circle" "3936.0495,900" "0.5")
(command "_circle" "3933.6974,897.6479" "0.5")
(command "_circle" "3931.3453,895.2959" "0.5")
(command "_circle" "3928.9933,892.9438" "0.5")
(command "_circle" "3926.6412,890.5917" "0.5")
(command "_circle" "3924.2891,888.2397" "0.5")
(command "_circle" "3921.9371,885.8876" "0.5")
(command "_layer" "set" "nitride" "")
(command "_block" "blkcoupler12" "3840,900" coupler12 "")
(command "_insert" "blkcoupler12" "3840,900" "1" "1" "0")
(command "_insert" "blkcoupler12" "3840,900" "1" "1" "180")
(command "_block" "blksinglenanobeam12" "3840,900" singlenanobeam12 "")
(command "_insert" "blksinglenanobeam12" "3840,900" "1" "1" "0")
(command "_insert" "blksinglenanobeam12" "3840,900" "1" "1" "180")
(command "_block" "blkanglednodearray12" "3840,900" anglednodearray12 "")
(command "_insert" "blkanglednodearray12" "3840,900" "1" "1" "0")
(command "_insert" "blkanglednodearray12" "3840,900" "1" "1" "180")
(command "_block" "blkcooledsinglenanobeam12" "3840,900" cooledsinglenanobeam12 "")
(command "_insert" "blkcooledsinglenanobeam12" "3840,900" "1" "1" "0")
(command "_insert" "blkcooledsinglenanobeam12" "3840,900" "1" "1" "180")
(command "_block" "blkyjunction12" "3840,900" yjunction12 "")
(command "_insert" "blkyjunction12" "3840,900" "1" "1" "0")
(command "_insert" "blkyjunction12" "3840,900" "1" "1" "180")
; DRAWING BULGING VEE GROOVE
(command "_layer" "set" "vgroove" "")
(setq coords (list 
(list 3765.415 -605) 
(list 3765.415 0) 
(list 3765.415 0) 
(list 3765.415 1800) 
(list 3765.415 1800) 
(list 3765.415 2405) 
(list 3914.585 2405) 
(list 3914.585 1800) 
(list 3914.585 1800) 
(list 3914.585 0) 
(list 3914.585 0) 
(list 3914.585 -605)))
(apply 'command (append '("pline") coords '("c")))
(command "._fillet" "radius" "0" "._fillet" "P" (entlast))
(command "_layer" "set" "window" "")
(command "_rectangle" "3765.415,-1935" "3914.585,-600")
(command "_rectangle" "3765.415,2400" "3914.585,5300")
(command "_layer" "set" "grid" "")
(command "_rectangle" "3766.415,-1934" "3789.9433,-1909.2133")
(command "_array" "last" "" "R" "75" "3" "25.7867" "24.5283")
(command "_rectangle" "3841,-1934" "3864.5283,-1909.2133")
(command "_array" "last" "" "R" "75" "3" "25.7867" "24.5283")
(command "_rectangle" "3766.415,1" "3789.9433,25.7")
(command "_array" "last" "" "R" "70" "3" "25.7" "24.5283")
(command "_rectangle" "3841,1" "3864.5283,25.7")
(command "_array" "last" "" "R" "70" "3" "25.7" "24.5283")
(command "_rectangle" "3766.415,1801" "3789.9433,1825.9185")
(command "_array" "last" "" "R" "135" "3" "25.9185" "24.5283")
(command "_rectangle" "3841,1801" "3864.5283,1825.9185")
(command "_array" "last" "" "R" "135" "3" "25.9185" "24.5283")
(command "_layer" "set" "vgrooveFDA" "")
(command "_rectangle" "3914.585,-2233" "3765.415,-1933")
(command "_layer" "set" "nitride" "")
(command "_layer" "set" "holes" "")
(command "_circle" "3917.085,331.5" "0.5")
(command "_array" "last" "" "R" "379" "1" "3" "2.5")
(command "_circle" "3762.915,331.5" "0.5")
(command "_array" "last" "" "R" "379" "1" "3" "-2.5")
(command "_layer" "set" "nitride" "")
(command "_layer" "set" "window" "")
(command "_layer" "set" "window" "")
(command "_rectangle" "3919.585,0" "4080.415,1800")
(command "._fillet" "radius" "20" "._fillet" "P" (entlast))
(command "_layer" "set" "grid" "")
(command "_rectangle" "3920.585,1" "3942.4179,25.7")
(command "_array" "last" "" "R" "70" "7" "25.7" "22.8329")
(command "_layer" "set" "nitride" "")
; DRAWING REGION LAYER
(command "_layer" "set" "regionLayer12" "")
(command "_rectangle" "3760,-460" "3920,2260")
(command "_layer" "set" "nitride" "")
(setq coupler12 nil)
(setq singlenanobeam12 nil)
(setq anglednodearray12 nil)
(setq cooledsinglenanobeam12 nil)
(setq yjunction12 nil)
; DEVICE #13
(command "_layer" "set" "window" "")
(command "_circle" "4072.915,-415" "5")
(command "_circle" "4072.915,-402.5" "5")
(command "_circle" "4072.915,-390" "5")
(command "_circle" "4072.915,-377.5" "5")
(command "_circle" "4060.415,-415" "5")
(command "_circle" "4060.415,-402.5" "5")
(command "_circle" "4060.415,-390" "5")
(command "_circle" "4060.415,-377.5" "5")
(command "_circle" "4047.915,-415" "5")
(command "_circle" "4047.915,-402.5" "5")
(command "_circle" "4047.915,-390" "5")
(command "_circle" "4047.915,-377.5" "5")
(command "_circle" "4035.415,-415" "5")
(command "_layer" "set" "nitride" "")
(setq currobj nil)
(setq currobj (ssadd))
; DRAWING COUPLER
(setq coords (list 
(list 4160.0645 -415) 
(list 4160.0645 -413) 
(list 4233.585 -413) 
(list 4233.585 -413) 
(list 4233.9677 -413.0761) 
(list 4234.2921 -413.2929) 
(list 4234.5089 -413.6173) 
(list 4234.585 -414) 
(list 4234.585 -411.8) 
(list 4234.585 -411.8) 
(list 4234.5089 -412.1827) 
(list 4234.2921 -412.5071) 
(list 4233.9677 -412.7239) 
(list 4233.585 -412.8) 
(list 4160.0645 -412.8) 
(list 4160.0645 -410.8) 
(list 4159.9355 -410.8) 
(list 4159.9355 -412.8) 
(list 4086.415 -412.8) 
(list 4086.0323 -412.7239) 
(list 4085.7079 -412.5071) 
(list 4085.4911 -412.1827) 
(list 4085.415 -411.8) 
(list 4085.415 -411.8) 
(list 4085.415 -414) 
(list 4085.4911 -413.6173) 
(list 4085.7079 -413.2929) 
(list 4086.0323 -413.0761) 
(list 4086.415 -413) 
(list 4086.415 -413) 
(list 4159.9355 -413) 
(list 4159.9355 -415)))
(apply 'command (append '("pline") coords '("c")))
(setq currobj (ssadd (entlast) currobj))
(command "._fillet" "radius" "0.3" "._fillet" "P" (entlast))
(command "_layer" "set" "holes" "")
(command "_circle" "4160,-412.9" "0.113")
(setq currobj (ssadd (entlast) currobj))
(command "_layer" "set" "nitride" "")
(command "_layer" "set" "text" "")
(command "_circle" "4159.2,-415" "0.075")
(command "_circle" "4159.2,-414.7" "0.075")
(command "_circle" "4159.2,-414.4" "0.075")
(command "_circle" "4158.9,-415" "0.075")
(command "_circle" "4158.9,-414.7" "0.075")
(command "_circle" "4158.9,-414.4" "0.075")
(command "_circle" "4158.6,-415" "0.075")
(command "_circle" "4158.6,-414.7" "0.075")
(command "_circle" "4158.6,-414.4" "0.075")
(command "_layer" "set" "nitride" "")
(command "_layer" "set" "prebias" "")
(command "_rectangle" "4085.415,-414" "4234.585,-411.8")
(setq currobj (ssadd (entlast) currobj))
(command "_rectangle" "4159.9355,-415" "4160.0645,-410.8")
(setq currobj (ssadd (entlast) currobj))
(command "_layer" "set" "nitride" "")
(setq coupler13 currobj)
(setq currobj nil)
(setq currobj (ssadd))
; DRAWING SINGLE NANOBEAM
(setq coords (list 
(list 4160.0645 -410.8) 
(list 4160.0645 -409.1417) 
(list 4160.0645 -407.4833) 
(list 4160.0645 -405.825) 
(list 4160.0645 -404.1667) 
(list 4160.0645 -402.5083) 
(list 4160.0645 -400.85) 
(list 4160.0645 -399.1917) 
(list 4160.0645 -397.5333) 
(list 4160.0646 -395.875) 
(list 4160.0646 -394.2167) 
(list 4160.0646 -392.5583) 
(list 4160.0646 -390.9) 
(list 4160.0647 -389.2417) 
(list 4160.0647 -387.5833) 
(list 4160.0647 -385.925) 
(list 4160.0648 -384.2667) 
(list 4160.0648 -382.6083) 
(list 4160.0649 -380.95) 
(list 4160.065 -379.2917) 
(list 4160.0651 -377.6333) 
(list 4160.0651 -375.975) 
(list 4160.0652 -374.3167) 
(list 4160.0653 -372.6583) 
(list 4160.0655 -371) 
(list 4160.0656 -369.3417) 
(list 4160.0657 -367.6833) 
(list 4160.0659 -366.025) 
(list 4160.066 -364.3667) 
(list 4160.0662 -362.7083) 
(list 4160.0664 -361.05) 
(list 4160.0666 -359.3917) 
(list 4160.0668 -357.7333) 
(list 4160.067 -356.075) 
(list 4160.0672 -354.4167) 
(list 4160.0675 -352.7583) 
(list 4160.0678 -351.1) 
(list 4160.068 -349.4417) 
(list 4160.0683 -347.7833) 
(list 4160.0686 -346.125) 
(list 4160.069 -344.4667) 
(list 4160.0693 -342.8083) 
(list 4160.0697 -341.15) 
(list 4160.07 -339.4917) 
(list 4160.0704 -337.8333) 
(list 4160.0709 -336.175) 
(list 4160.0713 -334.5167) 
(list 4160.0717 -332.8583) 
(list 4160.0722 -331.2) 
(list 4160.0727 -329.5417) 
(list 4160.0732 -327.8833) 
(list 4160.0737 -326.225) 
(list 4160.0743 -324.5667) 
(list 4160.0749 -322.9083) 
(list 4160.0755 -321.25) 
(list 4160.0761 -319.5917) 
(list 4160.0767 -317.9333) 
(list 4160.0774 -316.275) 
(list 4160.0781 -314.6167) 
(list 4160.0788 -312.9583) 
(list 4160.0796 -311.3) 
(list 4160.0803 -309.6417) 
(list 4160.0811 -307.9833) 
(list 4160.0819 -306.325) 
(list 4160.0828 -304.6667) 
(list 4160.0837 -303.0083) 
(list 4160.0845 -301.35) 
(list 4160.0855 -299.6917) 
(list 4160.0864 -298.0333) 
(list 4160.0874 -296.375) 
(list 4160.0884 -294.7167) 
(list 4160.0895 -293.0583) 
(list 4160.0905 -291.4) 
(list 4160.0916 -289.7417) 
(list 4160.0928 -288.0833) 
(list 4160.0939 -286.425) 
(list 4160.0951 -284.7667) 
(list 4160.0963 -283.1083) 
(list 4160.0976 -281.45) 
(list 4160.0989 -279.7917) 
(list 4160.1002 -278.1333) 
(list 4160.1016 -276.475) 
(list 4160.1029 -274.8167) 
(list 4160.1044 -273.1583) 
(list 4160.1058 -271.5) 
(list 4160.1073 -269.8417) 
(list 4160.1089 -268.1833) 
(list 4160.1104 -266.525) 
(list 4160.112 -264.8667) 
(list 4160.1137 -263.2083) 
(list 4160.1153 -261.55) 
(list 4160.117 -259.8917) 
(list 4160.1188 -258.2333) 
(list 4160.1206 -256.575) 
(list 4160.1224 -254.9167) 
(list 4160.1243 -253.2583) 
(list 4160.1262 -251.6) 
(list 4160.1281 -249.9417) 
(list 4160.1301 -248.2833) 
(list 4160.1322 -246.625) 
(list 4160.1342 -244.9667) 
(list 4160.1363 -243.3083) 
(list 4160.1385 -241.65) 
(list 4160.1407 -239.9917) 
(list 4160.1429 -238.3333) 
(list 4160.1452 -236.675) 
(list 4160.1476 -235.0167) 
(list 4160.1499 -233.3583) 
(list 4160.1523 -231.7) 
(list 4160.1548 -230.0417) 
(list 4160.1573 -228.3833) 
(list 4160.1599 -226.725) 
(list 4160.1625 -225.0667) 
(list 4160.1651 -223.4083) 
(list 4160.1678 -221.75) 
(list 4160.1706 -220.0917) 
(list 4160.1733 -218.4333) 
(list 4160.1762 -216.775) 
(list 4160.1791 -215.1167) 
(list 4160.182 -213.4583) 
(list 4160.185 -211.8) 
(list 4159.815 -211.8) 
(list 4159.818 -213.4583) 
(list 4159.8209 -215.1167) 
(list 4159.8238 -216.775) 
(list 4159.8267 -218.4333) 
(list 4159.8294 -220.0917) 
(list 4159.8322 -221.75) 
(list 4159.8349 -223.4083) 
(list 4159.8375 -225.0667) 
(list 4159.8401 -226.725) 
(list 4159.8427 -228.3833) 
(list 4159.8452 -230.0417) 
(list 4159.8477 -231.7) 
(list 4159.8501 -233.3583) 
(list 4159.8524 -235.0167) 
(list 4159.8548 -236.675) 
(list 4159.8571 -238.3333) 
(list 4159.8593 -239.9917) 
(list 4159.8615 -241.65) 
(list 4159.8637 -243.3083) 
(list 4159.8658 -244.9667) 
(list 4159.8678 -246.625) 
(list 4159.8699 -248.2833) 
(list 4159.8719 -249.9417) 
(list 4159.8738 -251.6) 
(list 4159.8757 -253.2583) 
(list 4159.8776 -254.9167) 
(list 4159.8794 -256.575) 
(list 4159.8812 -258.2333) 
(list 4159.883 -259.8917) 
(list 4159.8847 -261.55) 
(list 4159.8863 -263.2083) 
(list 4159.888 -264.8667) 
(list 4159.8896 -266.525) 
(list 4159.8911 -268.1833) 
(list 4159.8927 -269.8417) 
(list 4159.8942 -271.5) 
(list 4159.8956 -273.1583) 
(list 4159.8971 -274.8167) 
(list 4159.8984 -276.475) 
(list 4159.8998 -278.1333) 
(list 4159.9011 -279.7917) 
(list 4159.9024 -281.45) 
(list 4159.9037 -283.1083) 
(list 4159.9049 -284.7667) 
(list 4159.9061 -286.425) 
(list 4159.9072 -288.0833) 
(list 4159.9084 -289.7417) 
(list 4159.9095 -291.4) 
(list 4159.9105 -293.0583) 
(list 4159.9116 -294.7167) 
(list 4159.9126 -296.375) 
(list 4159.9136 -298.0333) 
(list 4159.9145 -299.6917) 
(list 4159.9155 -301.35) 
(list 4159.9163 -303.0083) 
(list 4159.9172 -304.6667) 
(list 4159.9181 -306.325) 
(list 4159.9189 -307.9833) 
(list 4159.9197 -309.6417) 
(list 4159.9204 -311.3) 
(list 4159.9212 -312.9583) 
(list 4159.9219 -314.6167) 
(list 4159.9226 -316.275) 
(list 4159.9233 -317.9333) 
(list 4159.9239 -319.5917) 
(list 4159.9245 -321.25) 
(list 4159.9251 -322.9083) 
(list 4159.9257 -324.5667) 
(list 4159.9263 -326.225) 
(list 4159.9268 -327.8833) 
(list 4159.9273 -329.5417) 
(list 4159.9278 -331.2) 
(list 4159.9283 -332.8583) 
(list 4159.9287 -334.5167) 
(list 4159.9291 -336.175) 
(list 4159.9296 -337.8333) 
(list 4159.93 -339.4917) 
(list 4159.9303 -341.15) 
(list 4159.9307 -342.8083) 
(list 4159.931 -344.4667) 
(list 4159.9314 -346.125) 
(list 4159.9317 -347.7833) 
(list 4159.932 -349.4417) 
(list 4159.9322 -351.1) 
(list 4159.9325 -352.7583) 
(list 4159.9328 -354.4167) 
(list 4159.933 -356.075) 
(list 4159.9332 -357.7333) 
(list 4159.9334 -359.3917) 
(list 4159.9336 -361.05) 
(list 4159.9338 -362.7083) 
(list 4159.934 -364.3667) 
(list 4159.9341 -366.025) 
(list 4159.9343 -367.6833) 
(list 4159.9344 -369.3417) 
(list 4159.9345 -371) 
(list 4159.9347 -372.6583) 
(list 4159.9348 -374.3167) 
(list 4159.9349 -375.975) 
(list 4159.9349 -377.6333) 
(list 4159.935 -379.2917) 
(list 4159.9351 -380.95) 
(list 4159.9352 -382.6083) 
(list 4159.9352 -384.2667) 
(list 4159.9353 -385.925) 
(list 4159.9353 -387.5833) 
(list 4159.9353 -389.2417) 
(list 4159.9354 -390.9) 
(list 4159.9354 -392.5583) 
(list 4159.9354 -394.2167) 
(list 4159.9354 -395.875) 
(list 4159.9355 -397.5333) 
(list 4159.9355 -399.1917) 
(list 4159.9355 -400.85) 
(list 4159.9355 -402.5083) 
(list 4159.9355 -404.1667) 
(list 4159.9355 -405.825) 
(list 4159.9355 -407.4833) 
(list 4159.9355 -409.1417) 
(list 4159.9355 -410.8)))
(apply 'command (append '("pline") coords '("c")))
(setq currobj (ssadd (entlast) currobj))
(command "_layer" "set" "prebias" "")
(command "_rectangle" "4159.815,-410.8" "4160.185,-211.8")
(setq currobj (ssadd (entlast) currobj))
(command "_layer" "set" "nitride" "")
(setq singlenanobeam13 currobj)
(setq currobj nil)
(setq currobj (ssadd))
; DRAWING NODE ARRAY
(setq coords (list 
(list 4160.185 -211.8) 
(list 4160.5625 -201.8) 
(list 4160.5625 -201.8) 
(list 4160.5625 -200.8) 
(list 4234.585 -212.6864) 
(list 4234.585 -207.7434) 
(list 4160.5625 -197.357) 
(list 4160.5625 -196.357) 
(list 4160.5625 -196.357) 
(list 4160.2625 -186.357) 
(list 4159.7375 -186.357) 
(list 4159.4375 -196.357) 
(list 4159.4375 -196.357) 
(list 4159.4375 -197.357) 
(list 4085.415 -207.7434) 
(list 4085.415 -212.6864) 
(list 4159.4375 -200.8) 
(list 4159.4375 -201.8) 
(list 4159.4375 -201.8) 
(list 4159.815 -211.8)))
(apply 'command (append '("pline") coords '("c")))
(setq currobj (ssadd (entlast) currobj))
(command "_layer" "set" "prebias" "")
(setq coords (list 
(list 4159.4375 -212.6864) 
(list 4159.4375 -200.8) 
(list 4085.415 -212.6864) 
(list 4085.415 -207.7434) 
(list 4159.4375 -197.357) 
(list 4159.4375 -186.357) 
(list 4160.5625 -186.357) 
(list 4160.5625 -197.357) 
(list 4234.585 -207.7434) 
(list 4234.585 -212.6864) 
(list 4160.5625 -200.8) 
(list 4160.5625 -212.6864)))
(apply 'command (append '("pline") coords '("c")))
(setq currobj (ssadd (entlast) currobj))
(command "_layer" "set" "nitride" "")
(command "_layer" "set" "fda1" "")
(setq coords (list 
(list 4160.5625 -200.657) 
(list 4234.585 -212.5434) 
(list 4234.585 -212.3664) 
(list 4160.5625 -200.58)))
(apply 'command (append '("pline") coords '("c")))
(setq currobj (ssadd (entlast) currobj))
(setq coords (list 
(list 4160.5625 -200.437) 
(list 4234.585 -212.2234) 
(list 4234.585 -212.0464) 
(list 4160.5625 -200.36)))
(apply 'command (append '("pline") coords '("c")))
(setq currobj (ssadd (entlast) currobj))
(setq coords (list 
(list 4160.5625 -200.217) 
(list 4234.585 -211.9034) 
(list 4234.585 -211.7264) 
(list 4160.5625 -200.14)))
(apply 'command (append '("pline") coords '("c")))
(setq currobj (ssadd (entlast) currobj))
(setq coords (list 
(list 4160.5625 -199.997) 
(list 4234.585 -211.5834) 
(list 4234.585 -211.4064) 
(list 4160.5625 -199.92)))
(apply 'command (append '("pline") coords '("c")))
(setq currobj (ssadd (entlast) currobj))
(setq coords (list 
(list 4160.5625 -199.777) 
(list 4234.585 -211.2634) 
(list 4234.585 -211.0864) 
(list 4160.5625 -199.7)))
(apply 'command (append '("pline") coords '("c")))
(setq currobj (ssadd (entlast) currobj))
(setq coords (list 
(list 4160.5625 -199.557) 
(list 4234.585 -210.9434) 
(list 4234.585 -210.7664) 
(list 4160.5625 -199.48)))
(apply 'command (append '("pline") coords '("c")))
(setq currobj (ssadd (entlast) currobj))
(setq coords (list 
(list 4160.5625 -199.337) 
(list 4234.585 -210.6234) 
(list 4234.585 -210.4464) 
(list 4160.5625 -199.26)))
(apply 'command (append '("pline") coords '("c")))
(setq currobj (ssadd (entlast) currobj))
(setq coords (list 
(list 4160.5625 -199.117) 
(list 4234.585 -210.3034) 
(list 4234.585 -210.1264) 
(list 4160.5625 -199.04)))
(apply 'command (append '("pline") coords '("c")))
(setq currobj (ssadd (entlast) currobj))
(setq coords (list 
(list 4160.5625 -198.897) 
(list 4234.585 -209.9834) 
(list 4234.585 -209.8064) 
(list 4160.5625 -198.82)))
(apply 'command (append '("pline") coords '("c")))
(setq currobj (ssadd (entlast) currobj))
(setq coords (list 
(list 4160.5625 -198.677) 
(list 4234.585 -209.6634) 
(list 4234.585 -209.4864) 
(list 4160.5625 -198.6)))
(apply 'command (append '("pline") coords '("c")))
(setq currobj (ssadd (entlast) currobj))
(setq coords (list 
(list 4160.5625 -198.457) 
(list 4234.585 -209.3434) 
(list 4234.585 -209.1664) 
(list 4160.5625 -198.38)))
(apply 'command (append '("pline") coords '("c")))
(setq currobj (ssadd (entlast) currobj))
(setq coords (list 
(list 4160.5625 -198.237) 
(list 4234.585 -209.0234) 
(list 4234.585 -208.8464) 
(list 4160.5625 -198.16)))
(apply 'command (append '("pline") coords '("c")))
(setq currobj (ssadd (entlast) currobj))
(setq coords (list 
(list 4160.5625 -198.017) 
(list 4234.585 -208.7034) 
(list 4234.585 -208.5264) 
(list 4160.5625 -197.94)))
(apply 'command (append '("pline") coords '("c")))
(setq currobj (ssadd (entlast) currobj))
(setq coords (list 
(list 4160.5625 -197.797) 
(list 4234.585 -208.3834) 
(list 4234.585 -208.2064) 
(list 4160.5625 -197.72)))
(apply 'command (append '("pline") coords '("c")))
(setq currobj (ssadd (entlast) currobj))
(setq coords (list 
(list 4160.5625 -197.577) 
(list 4234.585 -208.0634) 
(list 4234.585 -207.8864) 
(list 4160.5625 -197.5)))
(apply 'command (append '("pline") coords '("c")))
(setq currobj (ssadd (entlast) currobj))
(setq coords (list 
(list 4159.4375 -197.5) 
(list 4085.415 -207.8864) 
(list 4085.415 -208.0634) 
(list 4159.4375 -197.577)))
(apply 'command (append '("pline") coords '("c")))
(setq currobj (ssadd (entlast) currobj))
(setq coords (list 
(list 4159.4375 -197.72) 
(list 4085.415 -208.2064) 
(list 4085.415 -208.3834) 
(list 4159.4375 -197.797)))
(apply 'command (append '("pline") coords '("c")))
(setq currobj (ssadd (entlast) currobj))
(setq coords (list 
(list 4159.4375 -197.94) 
(list 4085.415 -208.5264) 
(list 4085.415 -208.7034) 
(list 4159.4375 -198.017)))
(apply 'command (append '("pline") coords '("c")))
(setq currobj (ssadd (entlast) currobj))
(setq coords (list 
(list 4159.4375 -198.16) 
(list 4085.415 -208.8464) 
(list 4085.415 -209.0234) 
(list 4159.4375 -198.237)))
(apply 'command (append '("pline") coords '("c")))
(setq currobj (ssadd (entlast) currobj))
(setq coords (list 
(list 4159.4375 -198.38) 
(list 4085.415 -209.1664) 
(list 4085.415 -209.3434) 
(list 4159.4375 -198.457)))
(apply 'command (append '("pline") coords '("c")))
(setq currobj (ssadd (entlast) currobj))
(setq coords (list 
(list 4159.4375 -198.6) 
(list 4085.415 -209.4864) 
(list 4085.415 -209.6634) 
(list 4159.4375 -198.677)))
(apply 'command (append '("pline") coords '("c")))
(setq currobj (ssadd (entlast) currobj))
(setq coords (list 
(list 4159.4375 -198.82) 
(list 4085.415 -209.8064) 
(list 4085.415 -209.9834) 
(list 4159.4375 -198.897)))
(apply 'command (append '("pline") coords '("c")))
(setq currobj (ssadd (entlast) currobj))
(setq coords (list 
(list 4159.4375 -199.04) 
(list 4085.415 -210.1264) 
(list 4085.415 -210.3034) 
(list 4159.4375 -199.117)))
(apply 'command (append '("pline") coords '("c")))
(setq currobj (ssadd (entlast) currobj))
(setq coords (list 
(list 4159.4375 -199.26) 
(list 4085.415 -210.4464) 
(list 4085.415 -210.6234) 
(list 4159.4375 -199.337)))
(apply 'command (append '("pline") coords '("c")))
(setq currobj (ssadd (entlast) currobj))
(setq coords (list 
(list 4159.4375 -199.48) 
(list 4085.415 -210.7664) 
(list 4085.415 -210.9434) 
(list 4159.4375 -199.557)))
(apply 'command (append '("pline") coords '("c")))
(setq currobj (ssadd (entlast) currobj))
(setq coords (list 
(list 4159.4375 -199.7) 
(list 4085.415 -211.0864) 
(list 4085.415 -211.2634) 
(list 4159.4375 -199.777)))
(apply 'command (append '("pline") coords '("c")))
(setq currobj (ssadd (entlast) currobj))
(setq coords (list 
(list 4159.4375 -199.92) 
(list 4085.415 -211.4064) 
(list 4085.415 -211.5834) 
(list 4159.4375 -199.997)))
(apply 'command (append '("pline") coords '("c")))
(setq currobj (ssadd (entlast) currobj))
(setq coords (list 
(list 4159.4375 -200.14) 
(list 4085.415 -211.7264) 
(list 4085.415 -211.9034) 
(list 4159.4375 -200.217)))
(apply 'command (append '("pline") coords '("c")))
(setq currobj (ssadd (entlast) currobj))
(setq coords (list 
(list 4159.4375 -200.36) 
(list 4085.415 -212.0464) 
(list 4085.415 -212.2234) 
(list 4159.4375 -200.437)))
(apply 'command (append '("pline") coords '("c")))
(setq currobj (ssadd (entlast) currobj))
(setq coords (list 
(list 4159.4375 -200.58) 
(list 4085.415 -212.3664) 
(list 4085.415 -212.5434) 
(list 4159.4375 -200.657)))
(apply 'command (append '("pline") coords '("c")))
(setq currobj (ssadd (entlast) currobj))
(command "_layer" "set" "nitride" "")
(command "_layer" "set" "text" "")
(command "_circle" "4158.985,-211.8" "0.075")
(command "_circle" "4158.985,-211.5" "0.075")
(command "_circle" "4158.985,-211.2" "0.075")
(command "_circle" "4158.985,-210.9" "0.075")
(command "_circle" "4158.985,-210.6" "0.075")
(command "_circle" "4158.685,-211.8" "0.075")
(command "_circle" "4158.685,-211.5" "0.075")
(command "_circle" "4158.685,-211.2" "0.075")
(command "_circle" "4158.685,-210.9" "0.075")
(command "_circle" "4158.685,-210.6" "0.075")
(command "_circle" "4158.385,-211.8" "0.075")
(command "_circle" "4158.385,-211.5" "0.075")
(command "_circle" "4158.385,-211.2" "0.075")
(command "_circle" "4158.385,-210.9" "0.075")
(command "_circle" "4158.385,-210.6" "0.075")
(command "_circle" "4158.085,-211.8" "0.075")
(command "_circle" "4158.085,-211.5" "0.075")
(command "_circle" "4158.085,-211.2" "0.075")
(command "_circle" "4158.085,-210.9" "0.075")
(command "_circle" "4158.085,-210.6" "0.075")
(command "_circle" "4157.785,-211.8" "0.075")
(command "_circle" "4157.785,-211.5" "0.075")
(command "_circle" "4157.785,-211.2" "0.075")
(command "_circle" "4157.785,-210.9" "0.075")
(command "_circle" "4157.785,-210.6" "0.075")
(command "_layer" "set" "nitride" "")
(setq anglednodearray13 currobj)
(setq currobj nil)
(setq currobj (ssadd))
; DRAWING COOLED SINGLE NANOBEAM
(setq coords (list 
(list 4160.2625 -186.357) 
(list 4160.2625 -181.357) 
(list 4159.7375 -181.357) 
(list 4159.7375 -186.357)))
(apply 'command (append '("pline") coords '("c")))
(setq currobj (ssadd (entlast) currobj))
(command "_layer" "set" "prebias" "")
(command "_rectangle" "4159.7375,-186.357" "4160.2625,-181.357")
(setq currobj (ssadd (entlast) currobj))
(command "_layer" "set" "nitride" "")
(setq coords (list 
(list 4160.2625 -181.357) 
(list 4160.5625 -171.357) 
(list 4160.5625 -171.357) 
(list 4160.5625 -170.357) 
(list 4234.585 -171.107) 
(list 4234.585 -166.164) 
(list 4160.5625 -166.914) 
(list 4160.5625 -165.914) 
(list 4160.5625 -165.914) 
(list 4160.2625 -155.914) 
(list 4159.7375 -155.914) 
(list 4159.4375 -165.914) 
(list 4159.4375 -165.914) 
(list 4159.4375 -166.914) 
(list 4085.415 -166.164) 
(list 4085.415 -171.107) 
(list 4159.4375 -170.357) 
(list 4159.4375 -171.357) 
(list 4159.4375 -171.357) 
(list 4159.7375 -181.357)))
(apply 'command (append '("pline") coords '("c")))
(setq currobj (ssadd (entlast) currobj))
(command "_layer" "set" "prebias" "")
(setq coords (list 
(list 4159.4375 -181.357) 
(list 4159.4375 -170.357) 
(list 4085.415 -171.107) 
(list 4085.415 -166.164) 
(list 4159.4375 -166.914) 
(list 4159.4375 -155.914) 
(list 4160.5625 -155.914) 
(list 4160.5625 -166.914) 
(list 4234.585 -166.164) 
(list 4234.585 -171.107) 
(list 4160.5625 -170.357) 
(list 4160.5625 -181.357)))
(apply 'command (append '("pline") coords '("c")))
(setq currobj (ssadd (entlast) currobj))
(command "_layer" "set" "nitride" "")
(command "_layer" "set" "fda1" "")
(setq coords (list 
(list 4160.5625 -170.214) 
(list 4234.585 -170.964) 
(list 4234.585 -170.787) 
(list 4160.5625 -170.137)))
(apply 'command (append '("pline") coords '("c")))
(setq currobj (ssadd (entlast) currobj))
(setq coords (list 
(list 4160.5625 -169.994) 
(list 4234.585 -170.644) 
(list 4234.585 -170.467) 
(list 4160.5625 -169.917)))
(apply 'command (append '("pline") coords '("c")))
(setq currobj (ssadd (entlast) currobj))
(setq coords (list 
(list 4160.5625 -169.774) 
(list 4234.585 -170.324) 
(list 4234.585 -170.147) 
(list 4160.5625 -169.697)))
(apply 'command (append '("pline") coords '("c")))
(setq currobj (ssadd (entlast) currobj))
(setq coords (list 
(list 4160.5625 -169.554) 
(list 4234.585 -170.004) 
(list 4234.585 -169.827) 
(list 4160.5625 -169.477)))
(apply 'command (append '("pline") coords '("c")))
(setq currobj (ssadd (entlast) currobj))
(setq coords (list 
(list 4160.5625 -169.334) 
(list 4234.585 -169.684) 
(list 4234.585 -169.507) 
(list 4160.5625 -169.257)))
(apply 'command (append '("pline") coords '("c")))
(setq currobj (ssadd (entlast) currobj))
(setq coords (list 
(list 4160.5625 -169.114) 
(list 4234.585 -169.364) 
(list 4234.585 -169.187) 
(list 4160.5625 -169.037)))
(apply 'command (append '("pline") coords '("c")))
(setq currobj (ssadd (entlast) currobj))
(setq coords (list 
(list 4160.5625 -168.894) 
(list 4234.585 -169.044) 
(list 4234.585 -168.867) 
(list 4160.5625 -168.817)))
(apply 'command (append '("pline") coords '("c")))
(setq currobj (ssadd (entlast) currobj))
(setq coords (list 
(list 4160.5625 -168.674) 
(list 4234.585 -168.724) 
(list 4234.585 -168.547) 
(list 4160.5625 -168.597)))
(apply 'command (append '("pline") coords '("c")))
(setq currobj (ssadd (entlast) currobj))
(setq coords (list 
(list 4160.5625 -168.454) 
(list 4234.585 -168.404) 
(list 4234.585 -168.227) 
(list 4160.5625 -168.377)))
(apply 'command (append '("pline") coords '("c")))
(setq currobj (ssadd (entlast) currobj))
(setq coords (list 
(list 4160.5625 -168.234) 
(list 4234.585 -168.084) 
(list 4234.585 -167.907) 
(list 4160.5625 -168.157)))
(apply 'command (append '("pline") coords '("c")))
(setq currobj (ssadd (entlast) currobj))
(setq coords (list 
(list 4160.5625 -168.014) 
(list 4234.585 -167.764) 
(list 4234.585 -167.587) 
(list 4160.5625 -167.937)))
(apply 'command (append '("pline") coords '("c")))
(setq currobj (ssadd (entlast) currobj))
(setq coords (list 
(list 4160.5625 -167.794) 
(list 4234.585 -167.444) 
(list 4234.585 -167.267) 
(list 4160.5625 -167.717)))
(apply 'command (append '("pline") coords '("c")))
(setq currobj (ssadd (entlast) currobj))
(setq coords (list 
(list 4160.5625 -167.574) 
(list 4234.585 -167.124) 
(list 4234.585 -166.947) 
(list 4160.5625 -167.497)))
(apply 'command (append '("pline") coords '("c")))
(setq currobj (ssadd (entlast) currobj))
(setq coords (list 
(list 4160.5625 -167.354) 
(list 4234.585 -166.804) 
(list 4234.585 -166.627) 
(list 4160.5625 -167.277)))
(apply 'command (append '("pline") coords '("c")))
(setq currobj (ssadd (entlast) currobj))
(setq coords (list 
(list 4160.5625 -167.134) 
(list 4234.585 -166.484) 
(list 4234.585 -166.307) 
(list 4160.5625 -167.057)))
(apply 'command (append '("pline") coords '("c")))
(setq currobj (ssadd (entlast) currobj))
(setq coords (list 
(list 4159.4375 -167.057) 
(list 4085.415 -166.307) 
(list 4085.415 -166.484) 
(list 4159.4375 -167.134)))
(apply 'command (append '("pline") coords '("c")))
(setq currobj (ssadd (entlast) currobj))
(setq coords (list 
(list 4159.4375 -167.277) 
(list 4085.415 -166.627) 
(list 4085.415 -166.804) 
(list 4159.4375 -167.354)))
(apply 'command (append '("pline") coords '("c")))
(setq currobj (ssadd (entlast) currobj))
(setq coords (list 
(list 4159.4375 -167.497) 
(list 4085.415 -166.947) 
(list 4085.415 -167.124) 
(list 4159.4375 -167.574)))
(apply 'command (append '("pline") coords '("c")))
(setq currobj (ssadd (entlast) currobj))
(setq coords (list 
(list 4159.4375 -167.717) 
(list 4085.415 -167.267) 
(list 4085.415 -167.444) 
(list 4159.4375 -167.794)))
(apply 'command (append '("pline") coords '("c")))
(setq currobj (ssadd (entlast) currobj))
(setq coords (list 
(list 4159.4375 -167.937) 
(list 4085.415 -167.587) 
(list 4085.415 -167.764) 
(list 4159.4375 -168.014)))
(apply 'command (append '("pline") coords '("c")))
(setq currobj (ssadd (entlast) currobj))
(setq coords (list 
(list 4159.4375 -168.157) 
(list 4085.415 -167.907) 
(list 4085.415 -168.084) 
(list 4159.4375 -168.234)))
(apply 'command (append '("pline") coords '("c")))
(setq currobj (ssadd (entlast) currobj))
(setq coords (list 
(list 4159.4375 -168.377) 
(list 4085.415 -168.227) 
(list 4085.415 -168.404) 
(list 4159.4375 -168.454)))
(apply 'command (append '("pline") coords '("c")))
(setq currobj (ssadd (entlast) currobj))
(setq coords (list 
(list 4159.4375 -168.597) 
(list 4085.415 -168.547) 
(list 4085.415 -168.724) 
(list 4159.4375 -168.674)))
(apply 'command (append '("pline") coords '("c")))
(setq currobj (ssadd (entlast) currobj))
(setq coords (list 
(list 4159.4375 -168.817) 
(list 4085.415 -168.867) 
(list 4085.415 -169.044) 
(list 4159.4375 -168.894)))
(apply 'command (append '("pline") coords '("c")))
(setq currobj (ssadd (entlast) currobj))
(setq coords (list 
(list 4159.4375 -169.037) 
(list 4085.415 -169.187) 
(list 4085.415 -169.364) 
(list 4159.4375 -169.114)))
(apply 'command (append '("pline") coords '("c")))
(setq currobj (ssadd (entlast) currobj))
(setq coords (list 
(list 4159.4375 -169.257) 
(list 4085.415 -169.507) 
(list 4085.415 -169.684) 
(list 4159.4375 -169.334)))
(apply 'command (append '("pline") coords '("c")))
(setq currobj (ssadd (entlast) currobj))
(setq coords (list 
(list 4159.4375 -169.477) 
(list 4085.415 -169.827) 
(list 4085.415 -170.004) 
(list 4159.4375 -169.554)))
(apply 'command (append '("pline") coords '("c")))
(setq currobj (ssadd (entlast) currobj))
(setq coords (list 
(list 4159.4375 -169.697) 
(list 4085.415 -170.147) 
(list 4085.415 -170.324) 
(list 4159.4375 -169.774)))
(apply 'command (append '("pline") coords '("c")))
(setq currobj (ssadd (entlast) currobj))
(setq coords (list 
(list 4159.4375 -169.917) 
(list 4085.415 -170.467) 
(list 4085.415 -170.644) 
(list 4159.4375 -169.994)))
(apply 'command (append '("pline") coords '("c")))
(setq currobj (ssadd (entlast) currobj))
(setq coords (list 
(list 4159.4375 -170.137) 
(list 4085.415 -170.787) 
(list 4085.415 -170.964) 
(list 4159.4375 -170.214)))
(apply 'command (append '("pline") coords '("c")))
(setq currobj (ssadd (entlast) currobj))
(command "_layer" "set" "nitride" "")
(command "_layer" "set" "text" "")
(command "_circle" "4159.0625,-181.357" "0.075")
(command "_circle" "4159.0625,-181.057" "0.075")
(command "_circle" "4159.0625,-180.757" "0.075")
(command "_circle" "4159.0625,-180.457" "0.075")
(command "_circle" "4159.0625,-180.157" "0.075")
(command "_circle" "4158.7625,-181.357" "0.075")
(command "_circle" "4158.7625,-181.057" "0.075")
(command "_circle" "4158.7625,-180.757" "0.075")
(command "_circle" "4158.7625,-180.457" "0.075")
(command "_circle" "4158.7625,-180.157" "0.075")
(command "_circle" "4158.4625,-181.357" "0.075")
(command "_circle" "4158.4625,-181.057" "0.075")
(command "_circle" "4158.4625,-180.757" "0.075")
(command "_circle" "4158.4625,-180.457" "0.075")
(command "_circle" "4158.4625,-180.157" "0.075")
(command "_circle" "4158.1625,-181.357" "0.075")
(command "_circle" "4158.1625,-181.057" "0.075")
(command "_circle" "4158.1625,-180.757" "0.075")
(command "_circle" "4158.1625,-180.457" "0.075")
(command "_circle" "4158.1625,-180.157" "0.075")
(command "_circle" "4157.8625,-181.357" "0.075")
(command "_circle" "4157.8625,-181.057" "0.075")
(command "_circle" "4157.8625,-180.757" "0.075")
(command "_circle" "4157.8625,-180.457" "0.075")
(command "_circle" "4157.8625,-180.157" "0.075")
(command "_layer" "set" "nitride" "")
(setq coords (list 
(list 4160.2625 -155.914) 
(list 4160.2625 -40.2693) 
(list 4159.7375 -40.2693) 
(list 4159.7375 -155.914)))
(apply 'command (append '("pline") coords '("c")))
(setq currobj (ssadd (entlast) currobj))
(command "_layer" "set" "prebias" "")
(command "_rectangle" "4159.7375,-155.914" "4160.2625,-40.2693")
(setq currobj (ssadd (entlast) currobj))
(command "_layer" "set" "nitride" "")
(setq coords (list 
(list 4160.2625 -40.2693) 
(list 4160.5625 -30.2693) 
(list 4160.5625 -30.2693) 
(list 4160.5625 -29.2693) 
(list 4234.585 -30.0193) 
(list 4234.585 -25.0763) 
(list 4160.5625 -25.8263) 
(list 4160.5625 -24.8263) 
(list 4160.5625 -24.8263) 
(list 4160.2625 -14.8263) 
(list 4159.7375 -14.8263) 
(list 4159.4375 -24.8263) 
(list 4159.4375 -24.8263) 
(list 4159.4375 -25.8263) 
(list 4085.415 -25.0763) 
(list 4085.415 -30.0193) 
(list 4159.4375 -29.2693) 
(list 4159.4375 -30.2693) 
(list 4159.4375 -30.2693) 
(list 4159.7375 -40.2693)))
(apply 'command (append '("pline") coords '("c")))
(setq currobj (ssadd (entlast) currobj))
(command "_layer" "set" "prebias" "")
(setq coords (list 
(list 4159.4375 -40.2693) 
(list 4159.4375 -29.2693) 
(list 4085.415 -30.0193) 
(list 4085.415 -25.0763) 
(list 4159.4375 -25.8263) 
(list 4159.4375 -14.8263) 
(list 4160.5625 -14.8263) 
(list 4160.5625 -25.8263) 
(list 4234.585 -25.0763) 
(list 4234.585 -30.0193) 
(list 4160.5625 -29.2693) 
(list 4160.5625 -40.2693)))
(apply 'command (append '("pline") coords '("c")))
(setq currobj (ssadd (entlast) currobj))
(command "_layer" "set" "nitride" "")
(command "_layer" "set" "fda1" "")
(setq coords (list 
(list 4160.5625 -29.1263) 
(list 4234.585 -29.8763) 
(list 4234.585 -29.6993) 
(list 4160.5625 -29.0493)))
(apply 'command (append '("pline") coords '("c")))
(setq currobj (ssadd (entlast) currobj))
(setq coords (list 
(list 4160.5625 -28.9063) 
(list 4234.585 -29.5563) 
(list 4234.585 -29.3793) 
(list 4160.5625 -28.8293)))
(apply 'command (append '("pline") coords '("c")))
(setq currobj (ssadd (entlast) currobj))
(setq coords (list 
(list 4160.5625 -28.6863) 
(list 4234.585 -29.2363) 
(list 4234.585 -29.0593) 
(list 4160.5625 -28.6093)))
(apply 'command (append '("pline") coords '("c")))
(setq currobj (ssadd (entlast) currobj))
(setq coords (list 
(list 4160.5625 -28.4663) 
(list 4234.585 -28.9163) 
(list 4234.585 -28.7393) 
(list 4160.5625 -28.3893)))
(apply 'command (append '("pline") coords '("c")))
(setq currobj (ssadd (entlast) currobj))
(setq coords (list 
(list 4160.5625 -28.2463) 
(list 4234.585 -28.5963) 
(list 4234.585 -28.4193) 
(list 4160.5625 -28.1693)))
(apply 'command (append '("pline") coords '("c")))
(setq currobj (ssadd (entlast) currobj))
(setq coords (list 
(list 4160.5625 -28.0263) 
(list 4234.585 -28.2763) 
(list 4234.585 -28.0993) 
(list 4160.5625 -27.9493)))
(apply 'command (append '("pline") coords '("c")))
(setq currobj (ssadd (entlast) currobj))
(setq coords (list 
(list 4160.5625 -27.8063) 
(list 4234.585 -27.9563) 
(list 4234.585 -27.7793) 
(list 4160.5625 -27.7293)))
(apply 'command (append '("pline") coords '("c")))
(setq currobj (ssadd (entlast) currobj))
(setq coords (list 
(list 4160.5625 -27.5863) 
(list 4234.585 -27.6363) 
(list 4234.585 -27.4593) 
(list 4160.5625 -27.5093)))
(apply 'command (append '("pline") coords '("c")))
(setq currobj (ssadd (entlast) currobj))
(setq coords (list 
(list 4160.5625 -27.3663) 
(list 4234.585 -27.3163) 
(list 4234.585 -27.1393) 
(list 4160.5625 -27.2893)))
(apply 'command (append '("pline") coords '("c")))
(setq currobj (ssadd (entlast) currobj))
(setq coords (list 
(list 4160.5625 -27.1463) 
(list 4234.585 -26.9963) 
(list 4234.585 -26.8193) 
(list 4160.5625 -27.0693)))
(apply 'command (append '("pline") coords '("c")))
(setq currobj (ssadd (entlast) currobj))
(setq coords (list 
(list 4160.5625 -26.9263) 
(list 4234.585 -26.6763) 
(list 4234.585 -26.4993) 
(list 4160.5625 -26.8493)))
(apply 'command (append '("pline") coords '("c")))
(setq currobj (ssadd (entlast) currobj))
(setq coords (list 
(list 4160.5625 -26.7063) 
(list 4234.585 -26.3563) 
(list 4234.585 -26.1793) 
(list 4160.5625 -26.6293)))
(apply 'command (append '("pline") coords '("c")))
(setq currobj (ssadd (entlast) currobj))
(setq coords (list 
(list 4160.5625 -26.4863) 
(list 4234.585 -26.0363) 
(list 4234.585 -25.8593) 
(list 4160.5625 -26.4093)))
(apply 'command (append '("pline") coords '("c")))
(setq currobj (ssadd (entlast) currobj))
(setq coords (list 
(list 4160.5625 -26.2663) 
(list 4234.585 -25.7163) 
(list 4234.585 -25.5393) 
(list 4160.5625 -26.1893)))
(apply 'command (append '("pline") coords '("c")))
(setq currobj (ssadd (entlast) currobj))
(setq coords (list 
(list 4160.5625 -26.0463) 
(list 4234.585 -25.3963) 
(list 4234.585 -25.2193) 
(list 4160.5625 -25.9693)))
(apply 'command (append '("pline") coords '("c")))
(setq currobj (ssadd (entlast) currobj))
(setq coords (list 
(list 4159.4375 -25.9693) 
(list 4085.415 -25.2193) 
(list 4085.415 -25.3963) 
(list 4159.4375 -26.0463)))
(apply 'command (append '("pline") coords '("c")))
(setq currobj (ssadd (entlast) currobj))
(setq coords (list 
(list 4159.4375 -26.1893) 
(list 4085.415 -25.5393) 
(list 4085.415 -25.7163) 
(list 4159.4375 -26.2663)))
(apply 'command (append '("pline") coords '("c")))
(setq currobj (ssadd (entlast) currobj))
(setq coords (list 
(list 4159.4375 -26.4093) 
(list 4085.415 -25.8593) 
(list 4085.415 -26.0363) 
(list 4159.4375 -26.4863)))
(apply 'command (append '("pline") coords '("c")))
(setq currobj (ssadd (entlast) currobj))
(setq coords (list 
(list 4159.4375 -26.6293) 
(list 4085.415 -26.1793) 
(list 4085.415 -26.3563) 
(list 4159.4375 -26.7063)))
(apply 'command (append '("pline") coords '("c")))
(setq currobj (ssadd (entlast) currobj))
(setq coords (list 
(list 4159.4375 -26.8493) 
(list 4085.415 -26.4993) 
(list 4085.415 -26.6763) 
(list 4159.4375 -26.9263)))
(apply 'command (append '("pline") coords '("c")))
(setq currobj (ssadd (entlast) currobj))
(setq coords (list 
(list 4159.4375 -27.0693) 
(list 4085.415 -26.8193) 
(list 4085.415 -26.9963) 
(list 4159.4375 -27.1463)))
(apply 'command (append '("pline") coords '("c")))
(setq currobj (ssadd (entlast) currobj))
(setq coords (list 
(list 4159.4375 -27.2893) 
(list 4085.415 -27.1393) 
(list 4085.415 -27.3163) 
(list 4159.4375 -27.3663)))
(apply 'command (append '("pline") coords '("c")))
(setq currobj (ssadd (entlast) currobj))
(setq coords (list 
(list 4159.4375 -27.5093) 
(list 4085.415 -27.4593) 
(list 4085.415 -27.6363) 
(list 4159.4375 -27.5863)))
(apply 'command (append '("pline") coords '("c")))
(setq currobj (ssadd (entlast) currobj))
(setq coords (list 
(list 4159.4375 -27.7293) 
(list 4085.415 -27.7793) 
(list 4085.415 -27.9563) 
(list 4159.4375 -27.8063)))
(apply 'command (append '("pline") coords '("c")))
(setq currobj (ssadd (entlast) currobj))
(setq coords (list 
(list 4159.4375 -27.9493) 
(list 4085.415 -28.0993) 
(list 4085.415 -28.2763) 
(list 4159.4375 -28.0263)))
(apply 'command (append '("pline") coords '("c")))
(setq currobj (ssadd (entlast) currobj))
(setq coords (list 
(list 4159.4375 -28.1693) 
(list 4085.415 -28.4193) 
(list 4085.415 -28.5963) 
(list 4159.4375 -28.2463)))
(apply 'command (append '("pline") coords '("c")))
(setq currobj (ssadd (entlast) currobj))
(setq coords (list 
(list 4159.4375 -28.3893) 
(list 4085.415 -28.7393) 
(list 4085.415 -28.9163) 
(list 4159.4375 -28.4663)))
(apply 'command (append '("pline") coords '("c")))
(setq currobj (ssadd (entlast) currobj))
(setq coords (list 
(list 4159.4375 -28.6093) 
(list 4085.415 -29.0593) 
(list 4085.415 -29.2363) 
(list 4159.4375 -28.6863)))
(apply 'command (append '("pline") coords '("c")))
(setq currobj (ssadd (entlast) currobj))
(setq coords (list 
(list 4159.4375 -28.8293) 
(list 4085.415 -29.3793) 
(list 4085.415 -29.5563) 
(list 4159.4375 -28.9063)))
(apply 'command (append '("pline") coords '("c")))
(setq currobj (ssadd (entlast) currobj))
(setq coords (list 
(list 4159.4375 -29.0493) 
(list 4085.415 -29.6993) 
(list 4085.415 -29.8763) 
(list 4159.4375 -29.1263)))
(apply 'command (append '("pline") coords '("c")))
(setq currobj (ssadd (entlast) currobj))
(command "_layer" "set" "nitride" "")
(command "_layer" "set" "text" "")
(command "_circle" "4159.0625,-40.2693" "0.075")
(command "_circle" "4159.0625,-39.9693" "0.075")
(command "_circle" "4159.0625,-39.6693" "0.075")
(command "_circle" "4159.0625,-39.3693" "0.075")
(command "_circle" "4159.0625,-39.0693" "0.075")
(command "_circle" "4158.7625,-40.2693" "0.075")
(command "_circle" "4158.7625,-39.9693" "0.075")
(command "_circle" "4158.7625,-39.6693" "0.075")
(command "_circle" "4158.7625,-39.3693" "0.075")
(command "_circle" "4158.7625,-39.0693" "0.075")
(command "_circle" "4158.4625,-40.2693" "0.075")
(command "_circle" "4158.4625,-39.9693" "0.075")
(command "_circle" "4158.4625,-39.6693" "0.075")
(command "_circle" "4158.4625,-39.3693" "0.075")
(command "_circle" "4158.4625,-39.0693" "0.075")
(command "_circle" "4158.1625,-40.2693" "0.075")
(command "_circle" "4158.1625,-39.9693" "0.075")
(command "_circle" "4158.1625,-39.6693" "0.075")
(command "_circle" "4158.1625,-39.3693" "0.075")
(command "_circle" "4158.1625,-39.0693" "0.075")
(command "_circle" "4157.8625,-40.2693" "0.075")
(command "_circle" "4157.8625,-39.9693" "0.075")
(command "_circle" "4157.8625,-39.6693" "0.075")
(command "_circle" "4157.8625,-39.3693" "0.075")
(command "_circle" "4157.8625,-39.0693" "0.075")
(command "_layer" "set" "nitride" "")
(setq coords (list 
(list 4160.2625 -14.8263) 
(list 4160.2625 100.8184) 
(list 4159.7375 100.8184) 
(list 4159.7375 -14.8263)))
(apply 'command (append '("pline") coords '("c")))
(setq currobj (ssadd (entlast) currobj))
(command "_layer" "set" "prebias" "")
(command "_rectangle" "4159.7375,-14.8263" "4160.2625,100.8184")
(setq currobj (ssadd (entlast) currobj))
(command "_layer" "set" "nitride" "")
(setq coords (list 
(list 4160.2625 100.8184) 
(list 4160.5625 110.8184) 
(list 4160.5625 110.8184) 
(list 4160.5625 111.8184) 
(list 4234.585 111.0684) 
(list 4234.585 116.0114) 
(list 4160.5625 115.2614) 
(list 4160.5625 116.2614) 
(list 4160.5625 116.2614) 
(list 4160.2625 126.2614) 
(list 4159.7375 126.2614) 
(list 4159.4375 116.2614) 
(list 4159.4375 116.2614) 
(list 4159.4375 115.2614) 
(list 4085.415 116.0114) 
(list 4085.415 111.0684) 
(list 4159.4375 111.8184) 
(list 4159.4375 110.8184) 
(list 4159.4375 110.8184) 
(list 4159.7375 100.8184)))
(apply 'command (append '("pline") coords '("c")))
(setq currobj (ssadd (entlast) currobj))
(command "_layer" "set" "prebias" "")
(setq coords (list 
(list 4159.4375 100.8184) 
(list 4159.4375 111.8184) 
(list 4085.415 111.0684) 
(list 4085.415 116.0114) 
(list 4159.4375 115.2614) 
(list 4159.4375 126.2614) 
(list 4160.5625 126.2614) 
(list 4160.5625 115.2614) 
(list 4234.585 116.0114) 
(list 4234.585 111.0684) 
(list 4160.5625 111.8184) 
(list 4160.5625 100.8184)))
(apply 'command (append '("pline") coords '("c")))
(setq currobj (ssadd (entlast) currobj))
(command "_layer" "set" "nitride" "")
(command "_layer" "set" "fda1" "")
(setq coords (list 
(list 4160.5625 111.9614) 
(list 4234.585 111.2114) 
(list 4234.585 111.3884) 
(list 4160.5625 112.0384)))
(apply 'command (append '("pline") coords '("c")))
(setq currobj (ssadd (entlast) currobj))
(setq coords (list 
(list 4160.5625 112.1814) 
(list 4234.585 111.5314) 
(list 4234.585 111.7084) 
(list 4160.5625 112.2584)))
(apply 'command (append '("pline") coords '("c")))
(setq currobj (ssadd (entlast) currobj))
(setq coords (list 
(list 4160.5625 112.4014) 
(list 4234.585 111.8514) 
(list 4234.585 112.0284) 
(list 4160.5625 112.4784)))
(apply 'command (append '("pline") coords '("c")))
(setq currobj (ssadd (entlast) currobj))
(setq coords (list 
(list 4160.5625 112.6214) 
(list 4234.585 112.1714) 
(list 4234.585 112.3484) 
(list 4160.5625 112.6984)))
(apply 'command (append '("pline") coords '("c")))
(setq currobj (ssadd (entlast) currobj))
(setq coords (list 
(list 4160.5625 112.8414) 
(list 4234.585 112.4914) 
(list 4234.585 112.6684) 
(list 4160.5625 112.9184)))
(apply 'command (append '("pline") coords '("c")))
(setq currobj (ssadd (entlast) currobj))
(setq coords (list 
(list 4160.5625 113.0614) 
(list 4234.585 112.8114) 
(list 4234.585 112.9884) 
(list 4160.5625 113.1384)))
(apply 'command (append '("pline") coords '("c")))
(setq currobj (ssadd (entlast) currobj))
(setq coords (list 
(list 4160.5625 113.2814) 
(list 4234.585 113.1314) 
(list 4234.585 113.3084) 
(list 4160.5625 113.3584)))
(apply 'command (append '("pline") coords '("c")))
(setq currobj (ssadd (entlast) currobj))
(setq coords (list 
(list 4160.5625 113.5014) 
(list 4234.585 113.4514) 
(list 4234.585 113.6284) 
(list 4160.5625 113.5784)))
(apply 'command (append '("pline") coords '("c")))
(setq currobj (ssadd (entlast) currobj))
(setq coords (list 
(list 4160.5625 113.7214) 
(list 4234.585 113.7714) 
(list 4234.585 113.9484) 
(list 4160.5625 113.7984)))
(apply 'command (append '("pline") coords '("c")))
(setq currobj (ssadd (entlast) currobj))
(setq coords (list 
(list 4160.5625 113.9414) 
(list 4234.585 114.0914) 
(list 4234.585 114.2684) 
(list 4160.5625 114.0184)))
(apply 'command (append '("pline") coords '("c")))
(setq currobj (ssadd (entlast) currobj))
(setq coords (list 
(list 4160.5625 114.1614) 
(list 4234.585 114.4114) 
(list 4234.585 114.5884) 
(list 4160.5625 114.2384)))
(apply 'command (append '("pline") coords '("c")))
(setq currobj (ssadd (entlast) currobj))
(setq coords (list 
(list 4160.5625 114.3814) 
(list 4234.585 114.7314) 
(list 4234.585 114.9084) 
(list 4160.5625 114.4584)))
(apply 'command (append '("pline") coords '("c")))
(setq currobj (ssadd (entlast) currobj))
(setq coords (list 
(list 4160.5625 114.6014) 
(list 4234.585 115.0514) 
(list 4234.585 115.2284) 
(list 4160.5625 114.6784)))
(apply 'command (append '("pline") coords '("c")))
(setq currobj (ssadd (entlast) currobj))
(setq coords (list 
(list 4160.5625 114.8214) 
(list 4234.585 115.3714) 
(list 4234.585 115.5484) 
(list 4160.5625 114.8984)))
(apply 'command (append '("pline") coords '("c")))
(setq currobj (ssadd (entlast) currobj))
(setq coords (list 
(list 4160.5625 115.0414) 
(list 4234.585 115.6914) 
(list 4234.585 115.8684) 
(list 4160.5625 115.1184)))
(apply 'command (append '("pline") coords '("c")))
(setq currobj (ssadd (entlast) currobj))
(setq coords (list 
(list 4159.4375 115.1184) 
(list 4085.415 115.8684) 
(list 4085.415 115.6914) 
(list 4159.4375 115.0414)))
(apply 'command (append '("pline") coords '("c")))
(setq currobj (ssadd (entlast) currobj))
(setq coords (list 
(list 4159.4375 114.8984) 
(list 4085.415 115.5484) 
(list 4085.415 115.3714) 
(list 4159.4375 114.8214)))
(apply 'command (append '("pline") coords '("c")))
(setq currobj (ssadd (entlast) currobj))
(setq coords (list 
(list 4159.4375 114.6784) 
(list 4085.415 115.2284) 
(list 4085.415 115.0514) 
(list 4159.4375 114.6014)))
(apply 'command (append '("pline") coords '("c")))
(setq currobj (ssadd (entlast) currobj))
(setq coords (list 
(list 4159.4375 114.4584) 
(list 4085.415 114.9084) 
(list 4085.415 114.7314) 
(list 4159.4375 114.3814)))
(apply 'command (append '("pline") coords '("c")))
(setq currobj (ssadd (entlast) currobj))
(setq coords (list 
(list 4159.4375 114.2384) 
(list 4085.415 114.5884) 
(list 4085.415 114.4114) 
(list 4159.4375 114.1614)))
(apply 'command (append '("pline") coords '("c")))
(setq currobj (ssadd (entlast) currobj))
(setq coords (list 
(list 4159.4375 114.0184) 
(list 4085.415 114.2684) 
(list 4085.415 114.0914) 
(list 4159.4375 113.9414)))
(apply 'command (append '("pline") coords '("c")))
(setq currobj (ssadd (entlast) currobj))
(setq coords (list 
(list 4159.4375 113.7984) 
(list 4085.415 113.9484) 
(list 4085.415 113.7714) 
(list 4159.4375 113.7214)))
(apply 'command (append '("pline") coords '("c")))
(setq currobj (ssadd (entlast) currobj))
(setq coords (list 
(list 4159.4375 113.5784) 
(list 4085.415 113.6284) 
(list 4085.415 113.4514) 
(list 4159.4375 113.5014)))
(apply 'command (append '("pline") coords '("c")))
(setq currobj (ssadd (entlast) currobj))
(setq coords (list 
(list 4159.4375 113.3584) 
(list 4085.415 113.3084) 
(list 4085.415 113.1314) 
(list 4159.4375 113.2814)))
(apply 'command (append '("pline") coords '("c")))
(setq currobj (ssadd (entlast) currobj))
(setq coords (list 
(list 4159.4375 113.1384) 
(list 4085.415 112.9884) 
(list 4085.415 112.8114) 
(list 4159.4375 113.0614)))
(apply 'command (append '("pline") coords '("c")))
(setq currobj (ssadd (entlast) currobj))
(setq coords (list 
(list 4159.4375 112.9184) 
(list 4085.415 112.6684) 
(list 4085.415 112.4914) 
(list 4159.4375 112.8414)))
(apply 'command (append '("pline") coords '("c")))
(setq currobj (ssadd (entlast) currobj))
(setq coords (list 
(list 4159.4375 112.6984) 
(list 4085.415 112.3484) 
(list 4085.415 112.1714) 
(list 4159.4375 112.6214)))
(apply 'command (append '("pline") coords '("c")))
(setq currobj (ssadd (entlast) currobj))
(setq coords (list 
(list 4159.4375 112.4784) 
(list 4085.415 112.0284) 
(list 4085.415 111.8514) 
(list 4159.4375 112.4014)))
(apply 'command (append '("pline") coords '("c")))
(setq currobj (ssadd (entlast) currobj))
(setq coords (list 
(list 4159.4375 112.2584) 
(list 4085.415 111.7084) 
(list 4085.415 111.5314) 
(list 4159.4375 112.1814)))
(apply 'command (append '("pline") coords '("c")))
(setq currobj (ssadd (entlast) currobj))
(setq coords (list 
(list 4159.4375 112.0384) 
(list 4085.415 111.3884) 
(list 4085.415 111.2114) 
(list 4159.4375 111.9614)))
(apply 'command (append '("pline") coords '("c")))
(setq currobj (ssadd (entlast) currobj))
(command "_layer" "set" "nitride" "")
(command "_layer" "set" "text" "")
(command "_circle" "4159.0625,100.8184" "0.075")
(command "_circle" "4159.0625,101.1184" "0.075")
(command "_circle" "4159.0625,101.4184" "0.075")
(command "_circle" "4159.0625,101.7184" "0.075")
(command "_circle" "4159.0625,102.0184" "0.075")
(command "_circle" "4158.7625,100.8184" "0.075")
(command "_circle" "4158.7625,101.1184" "0.075")
(command "_circle" "4158.7625,101.4184" "0.075")
(command "_circle" "4158.7625,101.7184" "0.075")
(command "_circle" "4158.7625,102.0184" "0.075")
(command "_circle" "4158.4625,100.8184" "0.075")
(command "_circle" "4158.4625,101.1184" "0.075")
(command "_circle" "4158.4625,101.4184" "0.075")
(command "_circle" "4158.4625,101.7184" "0.075")
(command "_circle" "4158.4625,102.0184" "0.075")
(command "_circle" "4158.1625,100.8184" "0.075")
(command "_circle" "4158.1625,101.1184" "0.075")
(command "_circle" "4158.1625,101.4184" "0.075")
(command "_circle" "4158.1625,101.7184" "0.075")
(command "_circle" "4158.1625,102.0184" "0.075")
(command "_circle" "4157.8625,100.8184" "0.075")
(command "_circle" "4157.8625,101.1184" "0.075")
(command "_circle" "4157.8625,101.4184" "0.075")
(command "_circle" "4157.8625,101.7184" "0.075")
(command "_circle" "4157.8625,102.0184" "0.075")
(command "_layer" "set" "nitride" "")
(setq coords (list 
(list 4160.2625 126.2614) 
(list 4160.2625 241.9061) 
(list 4159.7375 241.9061) 
(list 4159.7375 126.2614)))
(apply 'command (append '("pline") coords '("c")))
(setq currobj (ssadd (entlast) currobj))
(command "_layer" "set" "prebias" "")
(command "_rectangle" "4159.7375,126.2614" "4160.2625,241.9061")
(setq currobj (ssadd (entlast) currobj))
(command "_layer" "set" "nitride" "")
(setq coords (list 
(list 4160.2625 241.9061) 
(list 4160.5625 251.9061) 
(list 4160.5625 251.9061) 
(list 4160.5625 252.9061) 
(list 4234.585 252.1561) 
(list 4234.585 257.0991) 
(list 4160.5625 256.3491) 
(list 4160.5625 257.3491) 
(list 4160.5625 257.3491) 
(list 4160.2625 267.3491) 
(list 4159.7375 267.3491) 
(list 4159.4375 257.3491) 
(list 4159.4375 257.3491) 
(list 4159.4375 256.3491) 
(list 4085.415 257.0991) 
(list 4085.415 252.1561) 
(list 4159.4375 252.9061) 
(list 4159.4375 251.9061) 
(list 4159.4375 251.9061) 
(list 4159.7375 241.9061)))
(apply 'command (append '("pline") coords '("c")))
(setq currobj (ssadd (entlast) currobj))
(command "_layer" "set" "prebias" "")
(setq coords (list 
(list 4159.4375 241.9061) 
(list 4159.4375 252.9061) 
(list 4085.415 252.1561) 
(list 4085.415 257.0991) 
(list 4159.4375 256.3491) 
(list 4159.4375 267.3491) 
(list 4160.5625 267.3491) 
(list 4160.5625 256.3491) 
(list 4234.585 257.0991) 
(list 4234.585 252.1561) 
(list 4160.5625 252.9061) 
(list 4160.5625 241.9061)))
(apply 'command (append '("pline") coords '("c")))
(setq currobj (ssadd (entlast) currobj))
(command "_layer" "set" "nitride" "")
(command "_layer" "set" "fda1" "")
(setq coords (list 
(list 4160.5625 253.0491) 
(list 4234.585 252.2991) 
(list 4234.585 252.4761) 
(list 4160.5625 253.1261)))
(apply 'command (append '("pline") coords '("c")))
(setq currobj (ssadd (entlast) currobj))
(setq coords (list 
(list 4160.5625 253.2691) 
(list 4234.585 252.6191) 
(list 4234.585 252.7961) 
(list 4160.5625 253.3461)))
(apply 'command (append '("pline") coords '("c")))
(setq currobj (ssadd (entlast) currobj))
(setq coords (list 
(list 4160.5625 253.4891) 
(list 4234.585 252.9391) 
(list 4234.585 253.1161) 
(list 4160.5625 253.5661)))
(apply 'command (append '("pline") coords '("c")))
(setq currobj (ssadd (entlast) currobj))
(setq coords (list 
(list 4160.5625 253.7091) 
(list 4234.585 253.2591) 
(list 4234.585 253.4361) 
(list 4160.5625 253.7861)))
(apply 'command (append '("pline") coords '("c")))
(setq currobj (ssadd (entlast) currobj))
(setq coords (list 
(list 4160.5625 253.9291) 
(list 4234.585 253.5791) 
(list 4234.585 253.7561) 
(list 4160.5625 254.0061)))
(apply 'command (append '("pline") coords '("c")))
(setq currobj (ssadd (entlast) currobj))
(setq coords (list 
(list 4160.5625 254.1491) 
(list 4234.585 253.8991) 
(list 4234.585 254.0761) 
(list 4160.5625 254.2261)))
(apply 'command (append '("pline") coords '("c")))
(setq currobj (ssadd (entlast) currobj))
(setq coords (list 
(list 4160.5625 254.3691) 
(list 4234.585 254.2191) 
(list 4234.585 254.3961) 
(list 4160.5625 254.4461)))
(apply 'command (append '("pline") coords '("c")))
(setq currobj (ssadd (entlast) currobj))
(setq coords (list 
(list 4160.5625 254.5891) 
(list 4234.585 254.5391) 
(list 4234.585 254.7161) 
(list 4160.5625 254.6661)))
(apply 'command (append '("pline") coords '("c")))
(setq currobj (ssadd (entlast) currobj))
(setq coords (list 
(list 4160.5625 254.8091) 
(list 4234.585 254.8591) 
(list 4234.585 255.0361) 
(list 4160.5625 254.8861)))
(apply 'command (append '("pline") coords '("c")))
(setq currobj (ssadd (entlast) currobj))
(setq coords (list 
(list 4160.5625 255.0291) 
(list 4234.585 255.1791) 
(list 4234.585 255.3561) 
(list 4160.5625 255.1061)))
(apply 'command (append '("pline") coords '("c")))
(setq currobj (ssadd (entlast) currobj))
(setq coords (list 
(list 4160.5625 255.2491) 
(list 4234.585 255.4991) 
(list 4234.585 255.6761) 
(list 4160.5625 255.3261)))
(apply 'command (append '("pline") coords '("c")))
(setq currobj (ssadd (entlast) currobj))
(setq coords (list 
(list 4160.5625 255.4691) 
(list 4234.585 255.8191) 
(list 4234.585 255.9961) 
(list 4160.5625 255.5461)))
(apply 'command (append '("pline") coords '("c")))
(setq currobj (ssadd (entlast) currobj))
(setq coords (list 
(list 4160.5625 255.6891) 
(list 4234.585 256.1391) 
(list 4234.585 256.3161) 
(list 4160.5625 255.7661)))
(apply 'command (append '("pline") coords '("c")))
(setq currobj (ssadd (entlast) currobj))
(setq coords (list 
(list 4160.5625 255.9091) 
(list 4234.585 256.4591) 
(list 4234.585 256.6361) 
(list 4160.5625 255.9861)))
(apply 'command (append '("pline") coords '("c")))
(setq currobj (ssadd (entlast) currobj))
(setq coords (list 
(list 4160.5625 256.1291) 
(list 4234.585 256.7791) 
(list 4234.585 256.9561) 
(list 4160.5625 256.2061)))
(apply 'command (append '("pline") coords '("c")))
(setq currobj (ssadd (entlast) currobj))
(setq coords (list 
(list 4159.4375 256.2061) 
(list 4085.415 256.9561) 
(list 4085.415 256.7791) 
(list 4159.4375 256.1291)))
(apply 'command (append '("pline") coords '("c")))
(setq currobj (ssadd (entlast) currobj))
(setq coords (list 
(list 4159.4375 255.9861) 
(list 4085.415 256.6361) 
(list 4085.415 256.4591) 
(list 4159.4375 255.9091)))
(apply 'command (append '("pline") coords '("c")))
(setq currobj (ssadd (entlast) currobj))
(setq coords (list 
(list 4159.4375 255.7661) 
(list 4085.415 256.3161) 
(list 4085.415 256.1391) 
(list 4159.4375 255.6891)))
(apply 'command (append '("pline") coords '("c")))
(setq currobj (ssadd (entlast) currobj))
(setq coords (list 
(list 4159.4375 255.5461) 
(list 4085.415 255.9961) 
(list 4085.415 255.8191) 
(list 4159.4375 255.4691)))
(apply 'command (append '("pline") coords '("c")))
(setq currobj (ssadd (entlast) currobj))
(setq coords (list 
(list 4159.4375 255.3261) 
(list 4085.415 255.6761) 
(list 4085.415 255.4991) 
(list 4159.4375 255.2491)))
(apply 'command (append '("pline") coords '("c")))
(setq currobj (ssadd (entlast) currobj))
(setq coords (list 
(list 4159.4375 255.1061) 
(list 4085.415 255.3561) 
(list 4085.415 255.1791) 
(list 4159.4375 255.0291)))
(apply 'command (append '("pline") coords '("c")))
(setq currobj (ssadd (entlast) currobj))
(setq coords (list 
(list 4159.4375 254.8861) 
(list 4085.415 255.0361) 
(list 4085.415 254.8591) 
(list 4159.4375 254.8091)))
(apply 'command (append '("pline") coords '("c")))
(setq currobj (ssadd (entlast) currobj))
(setq coords (list 
(list 4159.4375 254.6661) 
(list 4085.415 254.7161) 
(list 4085.415 254.5391) 
(list 4159.4375 254.5891)))
(apply 'command (append '("pline") coords '("c")))
(setq currobj (ssadd (entlast) currobj))
(setq coords (list 
(list 4159.4375 254.4461) 
(list 4085.415 254.3961) 
(list 4085.415 254.2191) 
(list 4159.4375 254.3691)))
(apply 'command (append '("pline") coords '("c")))
(setq currobj (ssadd (entlast) currobj))
(setq coords (list 
(list 4159.4375 254.2261) 
(list 4085.415 254.0761) 
(list 4085.415 253.8991) 
(list 4159.4375 254.1491)))
(apply 'command (append '("pline") coords '("c")))
(setq currobj (ssadd (entlast) currobj))
(setq coords (list 
(list 4159.4375 254.0061) 
(list 4085.415 253.7561) 
(list 4085.415 253.5791) 
(list 4159.4375 253.9291)))
(apply 'command (append '("pline") coords '("c")))
(setq currobj (ssadd (entlast) currobj))
(setq coords (list 
(list 4159.4375 253.7861) 
(list 4085.415 253.4361) 
(list 4085.415 253.2591) 
(list 4159.4375 253.7091)))
(apply 'command (append '("pline") coords '("c")))
(setq currobj (ssadd (entlast) currobj))
(setq coords (list 
(list 4159.4375 253.5661) 
(list 4085.415 253.1161) 
(list 4085.415 252.9391) 
(list 4159.4375 253.4891)))
(apply 'command (append '("pline") coords '("c")))
(setq currobj (ssadd (entlast) currobj))
(setq coords (list 
(list 4159.4375 253.3461) 
(list 4085.415 252.7961) 
(list 4085.415 252.6191) 
(list 4159.4375 253.2691)))
(apply 'command (append '("pline") coords '("c")))
(setq currobj (ssadd (entlast) currobj))
(setq coords (list 
(list 4159.4375 253.1261) 
(list 4085.415 252.4761) 
(list 4085.415 252.2991) 
(list 4159.4375 253.0491)))
(apply 'command (append '("pline") coords '("c")))
(setq currobj (ssadd (entlast) currobj))
(command "_layer" "set" "nitride" "")
(command "_layer" "set" "text" "")
(command "_circle" "4159.0625,241.9061" "0.075")
(command "_circle" "4159.0625,242.2061" "0.075")
(command "_circle" "4159.0625,242.5061" "0.075")
(command "_circle" "4159.0625,242.8061" "0.075")
(command "_circle" "4159.0625,243.1061" "0.075")
(command "_circle" "4158.7625,241.9061" "0.075")
(command "_circle" "4158.7625,242.2061" "0.075")
(command "_circle" "4158.7625,242.5061" "0.075")
(command "_circle" "4158.7625,242.8061" "0.075")
(command "_circle" "4158.7625,243.1061" "0.075")
(command "_circle" "4158.4625,241.9061" "0.075")
(command "_circle" "4158.4625,242.2061" "0.075")
(command "_circle" "4158.4625,242.5061" "0.075")
(command "_circle" "4158.4625,242.8061" "0.075")
(command "_circle" "4158.4625,243.1061" "0.075")
(command "_circle" "4158.1625,241.9061" "0.075")
(command "_circle" "4158.1625,242.2061" "0.075")
(command "_circle" "4158.1625,242.5061" "0.075")
(command "_circle" "4158.1625,242.8061" "0.075")
(command "_circle" "4158.1625,243.1061" "0.075")
(command "_circle" "4157.8625,241.9061" "0.075")
(command "_circle" "4157.8625,242.2061" "0.075")
(command "_circle" "4157.8625,242.5061" "0.075")
(command "_circle" "4157.8625,242.8061" "0.075")
(command "_circle" "4157.8625,243.1061" "0.075")
(command "_layer" "set" "nitride" "")
(setq coords (list 
(list 4160.2625 267.3491) 
(list 4160.2625 382.9939) 
(list 4159.7375 382.9939) 
(list 4159.7375 267.3491)))
(apply 'command (append '("pline") coords '("c")))
(setq currobj (ssadd (entlast) currobj))
(command "_layer" "set" "prebias" "")
(command "_rectangle" "4159.7375,267.3491" "4160.2625,382.9939")
(setq currobj (ssadd (entlast) currobj))
(command "_layer" "set" "nitride" "")
(setq coords (list 
(list 4160.2625 382.9939) 
(list 4160.5625 392.9939) 
(list 4160.5625 392.9939) 
(list 4160.5625 393.9939) 
(list 4234.585 393.2439) 
(list 4234.585 398.1869) 
(list 4160.5625 397.4369) 
(list 4160.5625 398.4369) 
(list 4160.5625 398.4369) 
(list 4160.2625 408.4369) 
(list 4159.7375 408.4369) 
(list 4159.4375 398.4369) 
(list 4159.4375 398.4369) 
(list 4159.4375 397.4369) 
(list 4085.415 398.1869) 
(list 4085.415 393.2439) 
(list 4159.4375 393.9939) 
(list 4159.4375 392.9939) 
(list 4159.4375 392.9939) 
(list 4159.7375 382.9939)))
(apply 'command (append '("pline") coords '("c")))
(setq currobj (ssadd (entlast) currobj))
(command "_layer" "set" "prebias" "")
(setq coords (list 
(list 4159.4375 382.9939) 
(list 4159.4375 393.9939) 
(list 4085.415 393.2439) 
(list 4085.415 398.1869) 
(list 4159.4375 397.4369) 
(list 4159.4375 408.4369) 
(list 4160.5625 408.4369) 
(list 4160.5625 397.4369) 
(list 4234.585 398.1869) 
(list 4234.585 393.2439) 
(list 4160.5625 393.9939) 
(list 4160.5625 382.9939)))
(apply 'command (append '("pline") coords '("c")))
(setq currobj (ssadd (entlast) currobj))
(command "_layer" "set" "nitride" "")
(command "_layer" "set" "fda1" "")
(setq coords (list 
(list 4160.5625 394.1369) 
(list 4234.585 393.3869) 
(list 4234.585 393.5639) 
(list 4160.5625 394.2139)))
(apply 'command (append '("pline") coords '("c")))
(setq currobj (ssadd (entlast) currobj))
(setq coords (list 
(list 4160.5625 394.3569) 
(list 4234.585 393.7069) 
(list 4234.585 393.8839) 
(list 4160.5625 394.4339)))
(apply 'command (append '("pline") coords '("c")))
(setq currobj (ssadd (entlast) currobj))
(setq coords (list 
(list 4160.5625 394.5769) 
(list 4234.585 394.0269) 
(list 4234.585 394.2039) 
(list 4160.5625 394.6539)))
(apply 'command (append '("pline") coords '("c")))
(setq currobj (ssadd (entlast) currobj))
(setq coords (list 
(list 4160.5625 394.7969) 
(list 4234.585 394.3469) 
(list 4234.585 394.5239) 
(list 4160.5625 394.8739)))
(apply 'command (append '("pline") coords '("c")))
(setq currobj (ssadd (entlast) currobj))
(setq coords (list 
(list 4160.5625 395.0169) 
(list 4234.585 394.6669) 
(list 4234.585 394.8439) 
(list 4160.5625 395.0939)))
(apply 'command (append '("pline") coords '("c")))
(setq currobj (ssadd (entlast) currobj))
(setq coords (list 
(list 4160.5625 395.2369) 
(list 4234.585 394.9869) 
(list 4234.585 395.1639) 
(list 4160.5625 395.3139)))
(apply 'command (append '("pline") coords '("c")))
(setq currobj (ssadd (entlast) currobj))
(setq coords (list 
(list 4160.5625 395.4569) 
(list 4234.585 395.3069) 
(list 4234.585 395.4839) 
(list 4160.5625 395.5339)))
(apply 'command (append '("pline") coords '("c")))
(setq currobj (ssadd (entlast) currobj))
(setq coords (list 
(list 4160.5625 395.6769) 
(list 4234.585 395.6269) 
(list 4234.585 395.8039) 
(list 4160.5625 395.7539)))
(apply 'command (append '("pline") coords '("c")))
(setq currobj (ssadd (entlast) currobj))
(setq coords (list 
(list 4160.5625 395.8969) 
(list 4234.585 395.9469) 
(list 4234.585 396.1239) 
(list 4160.5625 395.9739)))
(apply 'command (append '("pline") coords '("c")))
(setq currobj (ssadd (entlast) currobj))
(setq coords (list 
(list 4160.5625 396.1169) 
(list 4234.585 396.2669) 
(list 4234.585 396.4439) 
(list 4160.5625 396.1939)))
(apply 'command (append '("pline") coords '("c")))
(setq currobj (ssadd (entlast) currobj))
(setq coords (list 
(list 4160.5625 396.3369) 
(list 4234.585 396.5869) 
(list 4234.585 396.7639) 
(list 4160.5625 396.4139)))
(apply 'command (append '("pline") coords '("c")))
(setq currobj (ssadd (entlast) currobj))
(setq coords (list 
(list 4160.5625 396.5569) 
(list 4234.585 396.9069) 
(list 4234.585 397.0839) 
(list 4160.5625 396.6339)))
(apply 'command (append '("pline") coords '("c")))
(setq currobj (ssadd (entlast) currobj))
(setq coords (list 
(list 4160.5625 396.7769) 
(list 4234.585 397.2269) 
(list 4234.585 397.4039) 
(list 4160.5625 396.8539)))
(apply 'command (append '("pline") coords '("c")))
(setq currobj (ssadd (entlast) currobj))
(setq coords (list 
(list 4160.5625 396.9969) 
(list 4234.585 397.5469) 
(list 4234.585 397.7239) 
(list 4160.5625 397.0739)))
(apply 'command (append '("pline") coords '("c")))
(setq currobj (ssadd (entlast) currobj))
(setq coords (list 
(list 4160.5625 397.2169) 
(list 4234.585 397.8669) 
(list 4234.585 398.0439) 
(list 4160.5625 397.2939)))
(apply 'command (append '("pline") coords '("c")))
(setq currobj (ssadd (entlast) currobj))
(setq coords (list 
(list 4159.4375 397.2939) 
(list 4085.415 398.0439) 
(list 4085.415 397.8669) 
(list 4159.4375 397.2169)))
(apply 'command (append '("pline") coords '("c")))
(setq currobj (ssadd (entlast) currobj))
(setq coords (list 
(list 4159.4375 397.0739) 
(list 4085.415 397.7239) 
(list 4085.415 397.5469) 
(list 4159.4375 396.9969)))
(apply 'command (append '("pline") coords '("c")))
(setq currobj (ssadd (entlast) currobj))
(setq coords (list 
(list 4159.4375 396.8539) 
(list 4085.415 397.4039) 
(list 4085.415 397.2269) 
(list 4159.4375 396.7769)))
(apply 'command (append '("pline") coords '("c")))
(setq currobj (ssadd (entlast) currobj))
(setq coords (list 
(list 4159.4375 396.6339) 
(list 4085.415 397.0839) 
(list 4085.415 396.9069) 
(list 4159.4375 396.5569)))
(apply 'command (append '("pline") coords '("c")))
(setq currobj (ssadd (entlast) currobj))
(setq coords (list 
(list 4159.4375 396.4139) 
(list 4085.415 396.7639) 
(list 4085.415 396.5869) 
(list 4159.4375 396.3369)))
(apply 'command (append '("pline") coords '("c")))
(setq currobj (ssadd (entlast) currobj))
(setq coords (list 
(list 4159.4375 396.1939) 
(list 4085.415 396.4439) 
(list 4085.415 396.2669) 
(list 4159.4375 396.1169)))
(apply 'command (append '("pline") coords '("c")))
(setq currobj (ssadd (entlast) currobj))
(setq coords (list 
(list 4159.4375 395.9739) 
(list 4085.415 396.1239) 
(list 4085.415 395.9469) 
(list 4159.4375 395.8969)))
(apply 'command (append '("pline") coords '("c")))
(setq currobj (ssadd (entlast) currobj))
(setq coords (list 
(list 4159.4375 395.7539) 
(list 4085.415 395.8039) 
(list 4085.415 395.6269) 
(list 4159.4375 395.6769)))
(apply 'command (append '("pline") coords '("c")))
(setq currobj (ssadd (entlast) currobj))
(setq coords (list 
(list 4159.4375 395.5339) 
(list 4085.415 395.4839) 
(list 4085.415 395.3069) 
(list 4159.4375 395.4569)))
(apply 'command (append '("pline") coords '("c")))
(setq currobj (ssadd (entlast) currobj))
(setq coords (list 
(list 4159.4375 395.3139) 
(list 4085.415 395.1639) 
(list 4085.415 394.9869) 
(list 4159.4375 395.2369)))
(apply 'command (append '("pline") coords '("c")))
(setq currobj (ssadd (entlast) currobj))
(setq coords (list 
(list 4159.4375 395.0939) 
(list 4085.415 394.8439) 
(list 4085.415 394.6669) 
(list 4159.4375 395.0169)))
(apply 'command (append '("pline") coords '("c")))
(setq currobj (ssadd (entlast) currobj))
(setq coords (list 
(list 4159.4375 394.8739) 
(list 4085.415 394.5239) 
(list 4085.415 394.3469) 
(list 4159.4375 394.7969)))
(apply 'command (append '("pline") coords '("c")))
(setq currobj (ssadd (entlast) currobj))
(setq coords (list 
(list 4159.4375 394.6539) 
(list 4085.415 394.2039) 
(list 4085.415 394.0269) 
(list 4159.4375 394.5769)))
(apply 'command (append '("pline") coords '("c")))
(setq currobj (ssadd (entlast) currobj))
(setq coords (list 
(list 4159.4375 394.4339) 
(list 4085.415 393.8839) 
(list 4085.415 393.7069) 
(list 4159.4375 394.3569)))
(apply 'command (append '("pline") coords '("c")))
(setq currobj (ssadd (entlast) currobj))
(setq coords (list 
(list 4159.4375 394.2139) 
(list 4085.415 393.5639) 
(list 4085.415 393.3869) 
(list 4159.4375 394.1369)))
(apply 'command (append '("pline") coords '("c")))
(setq currobj (ssadd (entlast) currobj))
(command "_layer" "set" "nitride" "")
(command "_layer" "set" "text" "")
(command "_circle" "4159.0625,382.9939" "0.075")
(command "_circle" "4159.0625,383.2939" "0.075")
(command "_circle" "4159.0625,383.5939" "0.075")
(command "_circle" "4159.0625,383.8939" "0.075")
(command "_circle" "4159.0625,384.1939" "0.075")
(command "_circle" "4158.7625,382.9939" "0.075")
(command "_circle" "4158.7625,383.2939" "0.075")
(command "_circle" "4158.7625,383.5939" "0.075")
(command "_circle" "4158.7625,383.8939" "0.075")
(command "_circle" "4158.7625,384.1939" "0.075")
(command "_circle" "4158.4625,382.9939" "0.075")
(command "_circle" "4158.4625,383.2939" "0.075")
(command "_circle" "4158.4625,383.5939" "0.075")
(command "_circle" "4158.4625,383.8939" "0.075")
(command "_circle" "4158.4625,384.1939" "0.075")
(command "_circle" "4158.1625,382.9939" "0.075")
(command "_circle" "4158.1625,383.2939" "0.075")
(command "_circle" "4158.1625,383.5939" "0.075")
(command "_circle" "4158.1625,383.8939" "0.075")
(command "_circle" "4158.1625,384.1939" "0.075")
(command "_circle" "4157.8625,382.9939" "0.075")
(command "_circle" "4157.8625,383.2939" "0.075")
(command "_circle" "4157.8625,383.5939" "0.075")
(command "_circle" "4157.8625,383.8939" "0.075")
(command "_circle" "4157.8625,384.1939" "0.075")
(command "_layer" "set" "nitride" "")
(setq coords (list 
(list 4160.2625 408.4369) 
(list 4160.2625 524.0816) 
(list 4159.7375 524.0816) 
(list 4159.7375 408.4369)))
(apply 'command (append '("pline") coords '("c")))
(setq currobj (ssadd (entlast) currobj))
(command "_layer" "set" "prebias" "")
(command "_rectangle" "4159.7375,408.4369" "4160.2625,524.0816")
(setq currobj (ssadd (entlast) currobj))
(command "_layer" "set" "nitride" "")
(setq coords (list 
(list 4160.2625 524.0816) 
(list 4160.5625 534.0816) 
(list 4160.5625 534.0816) 
(list 4160.5625 535.0816) 
(list 4234.585 534.3316) 
(list 4234.585 539.2746) 
(list 4160.5625 538.5246) 
(list 4160.5625 539.5246) 
(list 4160.5625 539.5246) 
(list 4160.2625 549.5246) 
(list 4159.7375 549.5246) 
(list 4159.4375 539.5246) 
(list 4159.4375 539.5246) 
(list 4159.4375 538.5246) 
(list 4085.415 539.2746) 
(list 4085.415 534.3316) 
(list 4159.4375 535.0816) 
(list 4159.4375 534.0816) 
(list 4159.4375 534.0816) 
(list 4159.7375 524.0816)))
(apply 'command (append '("pline") coords '("c")))
(setq currobj (ssadd (entlast) currobj))
(command "_layer" "set" "prebias" "")
(setq coords (list 
(list 4159.4375 524.0816) 
(list 4159.4375 535.0816) 
(list 4085.415 534.3316) 
(list 4085.415 539.2746) 
(list 4159.4375 538.5246) 
(list 4159.4375 549.5246) 
(list 4160.5625 549.5246) 
(list 4160.5625 538.5246) 
(list 4234.585 539.2746) 
(list 4234.585 534.3316) 
(list 4160.5625 535.0816) 
(list 4160.5625 524.0816)))
(apply 'command (append '("pline") coords '("c")))
(setq currobj (ssadd (entlast) currobj))
(command "_layer" "set" "nitride" "")
(command "_layer" "set" "fda1" "")
(setq coords (list 
(list 4160.5625 535.2246) 
(list 4234.585 534.4746) 
(list 4234.585 534.6516) 
(list 4160.5625 535.3016)))
(apply 'command (append '("pline") coords '("c")))
(setq currobj (ssadd (entlast) currobj))
(setq coords (list 
(list 4160.5625 535.4446) 
(list 4234.585 534.7946) 
(list 4234.585 534.9716) 
(list 4160.5625 535.5216)))
(apply 'command (append '("pline") coords '("c")))
(setq currobj (ssadd (entlast) currobj))
(setq coords (list 
(list 4160.5625 535.6646) 
(list 4234.585 535.1146) 
(list 4234.585 535.2916) 
(list 4160.5625 535.7416)))
(apply 'command (append '("pline") coords '("c")))
(setq currobj (ssadd (entlast) currobj))
(setq coords (list 
(list 4160.5625 535.8846) 
(list 4234.585 535.4346) 
(list 4234.585 535.6116) 
(list 4160.5625 535.9616)))
(apply 'command (append '("pline") coords '("c")))
(setq currobj (ssadd (entlast) currobj))
(setq coords (list 
(list 4160.5625 536.1046) 
(list 4234.585 535.7546) 
(list 4234.585 535.9316) 
(list 4160.5625 536.1816)))
(apply 'command (append '("pline") coords '("c")))
(setq currobj (ssadd (entlast) currobj))
(setq coords (list 
(list 4160.5625 536.3246) 
(list 4234.585 536.0746) 
(list 4234.585 536.2516) 
(list 4160.5625 536.4016)))
(apply 'command (append '("pline") coords '("c")))
(setq currobj (ssadd (entlast) currobj))
(setq coords (list 
(list 4160.5625 536.5446) 
(list 4234.585 536.3946) 
(list 4234.585 536.5716) 
(list 4160.5625 536.6216)))
(apply 'command (append '("pline") coords '("c")))
(setq currobj (ssadd (entlast) currobj))
(setq coords (list 
(list 4160.5625 536.7646) 
(list 4234.585 536.7146) 
(list 4234.585 536.8916) 
(list 4160.5625 536.8416)))
(apply 'command (append '("pline") coords '("c")))
(setq currobj (ssadd (entlast) currobj))
(setq coords (list 
(list 4160.5625 536.9846) 
(list 4234.585 537.0346) 
(list 4234.585 537.2116) 
(list 4160.5625 537.0616)))
(apply 'command (append '("pline") coords '("c")))
(setq currobj (ssadd (entlast) currobj))
(setq coords (list 
(list 4160.5625 537.2046) 
(list 4234.585 537.3546) 
(list 4234.585 537.5316) 
(list 4160.5625 537.2816)))
(apply 'command (append '("pline") coords '("c")))
(setq currobj (ssadd (entlast) currobj))
(setq coords (list 
(list 4160.5625 537.4246) 
(list 4234.585 537.6746) 
(list 4234.585 537.8516) 
(list 4160.5625 537.5016)))
(apply 'command (append '("pline") coords '("c")))
(setq currobj (ssadd (entlast) currobj))
(setq coords (list 
(list 4160.5625 537.6446) 
(list 4234.585 537.9946) 
(list 4234.585 538.1716) 
(list 4160.5625 537.7216)))
(apply 'command (append '("pline") coords '("c")))
(setq currobj (ssadd (entlast) currobj))
(setq coords (list 
(list 4160.5625 537.8646) 
(list 4234.585 538.3146) 
(list 4234.585 538.4916) 
(list 4160.5625 537.9416)))
(apply 'command (append '("pline") coords '("c")))
(setq currobj (ssadd (entlast) currobj))
(setq coords (list 
(list 4160.5625 538.0846) 
(list 4234.585 538.6346) 
(list 4234.585 538.8116) 
(list 4160.5625 538.1616)))
(apply 'command (append '("pline") coords '("c")))
(setq currobj (ssadd (entlast) currobj))
(setq coords (list 
(list 4160.5625 538.3046) 
(list 4234.585 538.9546) 
(list 4234.585 539.1316) 
(list 4160.5625 538.3816)))
(apply 'command (append '("pline") coords '("c")))
(setq currobj (ssadd (entlast) currobj))
(setq coords (list 
(list 4159.4375 538.3816) 
(list 4085.415 539.1316) 
(list 4085.415 538.9546) 
(list 4159.4375 538.3046)))
(apply 'command (append '("pline") coords '("c")))
(setq currobj (ssadd (entlast) currobj))
(setq coords (list 
(list 4159.4375 538.1616) 
(list 4085.415 538.8116) 
(list 4085.415 538.6346) 
(list 4159.4375 538.0846)))
(apply 'command (append '("pline") coords '("c")))
(setq currobj (ssadd (entlast) currobj))
(setq coords (list 
(list 4159.4375 537.9416) 
(list 4085.415 538.4916) 
(list 4085.415 538.3146) 
(list 4159.4375 537.8646)))
(apply 'command (append '("pline") coords '("c")))
(setq currobj (ssadd (entlast) currobj))
(setq coords (list 
(list 4159.4375 537.7216) 
(list 4085.415 538.1716) 
(list 4085.415 537.9946) 
(list 4159.4375 537.6446)))
(apply 'command (append '("pline") coords '("c")))
(setq currobj (ssadd (entlast) currobj))
(setq coords (list 
(list 4159.4375 537.5016) 
(list 4085.415 537.8516) 
(list 4085.415 537.6746) 
(list 4159.4375 537.4246)))
(apply 'command (append '("pline") coords '("c")))
(setq currobj (ssadd (entlast) currobj))
(setq coords (list 
(list 4159.4375 537.2816) 
(list 4085.415 537.5316) 
(list 4085.415 537.3546) 
(list 4159.4375 537.2046)))
(apply 'command (append '("pline") coords '("c")))
(setq currobj (ssadd (entlast) currobj))
(setq coords (list 
(list 4159.4375 537.0616) 
(list 4085.415 537.2116) 
(list 4085.415 537.0346) 
(list 4159.4375 536.9846)))
(apply 'command (append '("pline") coords '("c")))
(setq currobj (ssadd (entlast) currobj))
(setq coords (list 
(list 4159.4375 536.8416) 
(list 4085.415 536.8916) 
(list 4085.415 536.7146) 
(list 4159.4375 536.7646)))
(apply 'command (append '("pline") coords '("c")))
(setq currobj (ssadd (entlast) currobj))
(setq coords (list 
(list 4159.4375 536.6216) 
(list 4085.415 536.5716) 
(list 4085.415 536.3946) 
(list 4159.4375 536.5446)))
(apply 'command (append '("pline") coords '("c")))
(setq currobj (ssadd (entlast) currobj))
(setq coords (list 
(list 4159.4375 536.4016) 
(list 4085.415 536.2516) 
(list 4085.415 536.0746) 
(list 4159.4375 536.3246)))
(apply 'command (append '("pline") coords '("c")))
(setq currobj (ssadd (entlast) currobj))
(setq coords (list 
(list 4159.4375 536.1816) 
(list 4085.415 535.9316) 
(list 4085.415 535.7546) 
(list 4159.4375 536.1046)))
(apply 'command (append '("pline") coords '("c")))
(setq currobj (ssadd (entlast) currobj))
(setq coords (list 
(list 4159.4375 535.9616) 
(list 4085.415 535.6116) 
(list 4085.415 535.4346) 
(list 4159.4375 535.8846)))
(apply 'command (append '("pline") coords '("c")))
(setq currobj (ssadd (entlast) currobj))
(setq coords (list 
(list 4159.4375 535.7416) 
(list 4085.415 535.2916) 
(list 4085.415 535.1146) 
(list 4159.4375 535.6646)))
(apply 'command (append '("pline") coords '("c")))
(setq currobj (ssadd (entlast) currobj))
(setq coords (list 
(list 4159.4375 535.5216) 
(list 4085.415 534.9716) 
(list 4085.415 534.7946) 
(list 4159.4375 535.4446)))
(apply 'command (append '("pline") coords '("c")))
(setq currobj (ssadd (entlast) currobj))
(setq coords (list 
(list 4159.4375 535.3016) 
(list 4085.415 534.6516) 
(list 4085.415 534.4746) 
(list 4159.4375 535.2246)))
(apply 'command (append '("pline") coords '("c")))
(setq currobj (ssadd (entlast) currobj))
(command "_layer" "set" "nitride" "")
(command "_layer" "set" "text" "")
(command "_circle" "4159.0625,524.0816" "0.075")
(command "_circle" "4159.0625,524.3816" "0.075")
(command "_circle" "4159.0625,524.6816" "0.075")
(command "_circle" "4159.0625,524.9816" "0.075")
(command "_circle" "4159.0625,525.2816" "0.075")
(command "_circle" "4158.7625,524.0816" "0.075")
(command "_circle" "4158.7625,524.3816" "0.075")
(command "_circle" "4158.7625,524.6816" "0.075")
(command "_circle" "4158.7625,524.9816" "0.075")
(command "_circle" "4158.7625,525.2816" "0.075")
(command "_circle" "4158.4625,524.0816" "0.075")
(command "_circle" "4158.4625,524.3816" "0.075")
(command "_circle" "4158.4625,524.6816" "0.075")
(command "_circle" "4158.4625,524.9816" "0.075")
(command "_circle" "4158.4625,525.2816" "0.075")
(command "_circle" "4158.1625,524.0816" "0.075")
(command "_circle" "4158.1625,524.3816" "0.075")
(command "_circle" "4158.1625,524.6816" "0.075")
(command "_circle" "4158.1625,524.9816" "0.075")
(command "_circle" "4158.1625,525.2816" "0.075")
(command "_circle" "4157.8625,524.0816" "0.075")
(command "_circle" "4157.8625,524.3816" "0.075")
(command "_circle" "4157.8625,524.6816" "0.075")
(command "_circle" "4157.8625,524.9816" "0.075")
(command "_circle" "4157.8625,525.2816" "0.075")
(command "_layer" "set" "nitride" "")
(setq coords (list 
(list 4160.2625 549.5246) 
(list 4160.2625 665.1693) 
(list 4159.7375 665.1693) 
(list 4159.7375 549.5246)))
(apply 'command (append '("pline") coords '("c")))
(setq currobj (ssadd (entlast) currobj))
(command "_layer" "set" "prebias" "")
(command "_rectangle" "4159.7375,549.5246" "4160.2625,665.1693")
(setq currobj (ssadd (entlast) currobj))
(command "_layer" "set" "nitride" "")
(setq coords (list 
(list 4160.2625 665.1693) 
(list 4160.5625 675.1693) 
(list 4160.5625 675.1693) 
(list 4160.5625 676.1693) 
(list 4234.585 675.4193) 
(list 4234.585 680.3623) 
(list 4160.5625 679.6123) 
(list 4160.5625 680.6123) 
(list 4160.5625 680.6123) 
(list 4160.2625 690.6123) 
(list 4159.7375 690.6123) 
(list 4159.4375 680.6123) 
(list 4159.4375 680.6123) 
(list 4159.4375 679.6123) 
(list 4085.415 680.3623) 
(list 4085.415 675.4193) 
(list 4159.4375 676.1693) 
(list 4159.4375 675.1693) 
(list 4159.4375 675.1693) 
(list 4159.7375 665.1693)))
(apply 'command (append '("pline") coords '("c")))
(setq currobj (ssadd (entlast) currobj))
(command "_layer" "set" "prebias" "")
(setq coords (list 
(list 4159.4375 665.1693) 
(list 4159.4375 676.1693) 
(list 4085.415 675.4193) 
(list 4085.415 680.3623) 
(list 4159.4375 679.6123) 
(list 4159.4375 690.6123) 
(list 4160.5625 690.6123) 
(list 4160.5625 679.6123) 
(list 4234.585 680.3623) 
(list 4234.585 675.4193) 
(list 4160.5625 676.1693) 
(list 4160.5625 665.1693)))
(apply 'command (append '("pline") coords '("c")))
(setq currobj (ssadd (entlast) currobj))
(command "_layer" "set" "nitride" "")
(command "_layer" "set" "fda1" "")
(setq coords (list 
(list 4160.5625 676.3123) 
(list 4234.585 675.5623) 
(list 4234.585 675.7393) 
(list 4160.5625 676.3893)))
(apply 'command (append '("pline") coords '("c")))
(setq currobj (ssadd (entlast) currobj))
(setq coords (list 
(list 4160.5625 676.5323) 
(list 4234.585 675.8823) 
(list 4234.585 676.0593) 
(list 4160.5625 676.6093)))
(apply 'command (append '("pline") coords '("c")))
(setq currobj (ssadd (entlast) currobj))
(setq coords (list 
(list 4160.5625 676.7523) 
(list 4234.585 676.2023) 
(list 4234.585 676.3793) 
(list 4160.5625 676.8293)))
(apply 'command (append '("pline") coords '("c")))
(setq currobj (ssadd (entlast) currobj))
(setq coords (list 
(list 4160.5625 676.9723) 
(list 4234.585 676.5223) 
(list 4234.585 676.6993) 
(list 4160.5625 677.0493)))
(apply 'command (append '("pline") coords '("c")))
(setq currobj (ssadd (entlast) currobj))
(setq coords (list 
(list 4160.5625 677.1923) 
(list 4234.585 676.8423) 
(list 4234.585 677.0193) 
(list 4160.5625 677.2693)))
(apply 'command (append '("pline") coords '("c")))
(setq currobj (ssadd (entlast) currobj))
(setq coords (list 
(list 4160.5625 677.4123) 
(list 4234.585 677.1623) 
(list 4234.585 677.3393) 
(list 4160.5625 677.4893)))
(apply 'command (append '("pline") coords '("c")))
(setq currobj (ssadd (entlast) currobj))
(setq coords (list 
(list 4160.5625 677.6323) 
(list 4234.585 677.4823) 
(list 4234.585 677.6593) 
(list 4160.5625 677.7093)))
(apply 'command (append '("pline") coords '("c")))
(setq currobj (ssadd (entlast) currobj))
(setq coords (list 
(list 4160.5625 677.8523) 
(list 4234.585 677.8023) 
(list 4234.585 677.9793) 
(list 4160.5625 677.9293)))
(apply 'command (append '("pline") coords '("c")))
(setq currobj (ssadd (entlast) currobj))
(setq coords (list 
(list 4160.5625 678.0723) 
(list 4234.585 678.1223) 
(list 4234.585 678.2993) 
(list 4160.5625 678.1493)))
(apply 'command (append '("pline") coords '("c")))
(setq currobj (ssadd (entlast) currobj))
(setq coords (list 
(list 4160.5625 678.2923) 
(list 4234.585 678.4423) 
(list 4234.585 678.6193) 
(list 4160.5625 678.3693)))
(apply 'command (append '("pline") coords '("c")))
(setq currobj (ssadd (entlast) currobj))
(setq coords (list 
(list 4160.5625 678.5123) 
(list 4234.585 678.7623) 
(list 4234.585 678.9393) 
(list 4160.5625 678.5893)))
(apply 'command (append '("pline") coords '("c")))
(setq currobj (ssadd (entlast) currobj))
(setq coords (list 
(list 4160.5625 678.7323) 
(list 4234.585 679.0823) 
(list 4234.585 679.2593) 
(list 4160.5625 678.8093)))
(apply 'command (append '("pline") coords '("c")))
(setq currobj (ssadd (entlast) currobj))
(setq coords (list 
(list 4160.5625 678.9523) 
(list 4234.585 679.4023) 
(list 4234.585 679.5793) 
(list 4160.5625 679.0293)))
(apply 'command (append '("pline") coords '("c")))
(setq currobj (ssadd (entlast) currobj))
(setq coords (list 
(list 4160.5625 679.1723) 
(list 4234.585 679.7223) 
(list 4234.585 679.8993) 
(list 4160.5625 679.2493)))
(apply 'command (append '("pline") coords '("c")))
(setq currobj (ssadd (entlast) currobj))
(setq coords (list 
(list 4160.5625 679.3923) 
(list 4234.585 680.0423) 
(list 4234.585 680.2193) 
(list 4160.5625 679.4693)))
(apply 'command (append '("pline") coords '("c")))
(setq currobj (ssadd (entlast) currobj))
(setq coords (list 
(list 4159.4375 679.4693) 
(list 4085.415 680.2193) 
(list 4085.415 680.0423) 
(list 4159.4375 679.3923)))
(apply 'command (append '("pline") coords '("c")))
(setq currobj (ssadd (entlast) currobj))
(setq coords (list 
(list 4159.4375 679.2493) 
(list 4085.415 679.8993) 
(list 4085.415 679.7223) 
(list 4159.4375 679.1723)))
(apply 'command (append '("pline") coords '("c")))
(setq currobj (ssadd (entlast) currobj))
(setq coords (list 
(list 4159.4375 679.0293) 
(list 4085.415 679.5793) 
(list 4085.415 679.4023) 
(list 4159.4375 678.9523)))
(apply 'command (append '("pline") coords '("c")))
(setq currobj (ssadd (entlast) currobj))
(setq coords (list 
(list 4159.4375 678.8093) 
(list 4085.415 679.2593) 
(list 4085.415 679.0823) 
(list 4159.4375 678.7323)))
(apply 'command (append '("pline") coords '("c")))
(setq currobj (ssadd (entlast) currobj))
(setq coords (list 
(list 4159.4375 678.5893) 
(list 4085.415 678.9393) 
(list 4085.415 678.7623) 
(list 4159.4375 678.5123)))
(apply 'command (append '("pline") coords '("c")))
(setq currobj (ssadd (entlast) currobj))
(setq coords (list 
(list 4159.4375 678.3693) 
(list 4085.415 678.6193) 
(list 4085.415 678.4423) 
(list 4159.4375 678.2923)))
(apply 'command (append '("pline") coords '("c")))
(setq currobj (ssadd (entlast) currobj))
(setq coords (list 
(list 4159.4375 678.1493) 
(list 4085.415 678.2993) 
(list 4085.415 678.1223) 
(list 4159.4375 678.0723)))
(apply 'command (append '("pline") coords '("c")))
(setq currobj (ssadd (entlast) currobj))
(setq coords (list 
(list 4159.4375 677.9293) 
(list 4085.415 677.9793) 
(list 4085.415 677.8023) 
(list 4159.4375 677.8523)))
(apply 'command (append '("pline") coords '("c")))
(setq currobj (ssadd (entlast) currobj))
(setq coords (list 
(list 4159.4375 677.7093) 
(list 4085.415 677.6593) 
(list 4085.415 677.4823) 
(list 4159.4375 677.6323)))
(apply 'command (append '("pline") coords '("c")))
(setq currobj (ssadd (entlast) currobj))
(setq coords (list 
(list 4159.4375 677.4893) 
(list 4085.415 677.3393) 
(list 4085.415 677.1623) 
(list 4159.4375 677.4123)))
(apply 'command (append '("pline") coords '("c")))
(setq currobj (ssadd (entlast) currobj))
(setq coords (list 
(list 4159.4375 677.2693) 
(list 4085.415 677.0193) 
(list 4085.415 676.8423) 
(list 4159.4375 677.1923)))
(apply 'command (append '("pline") coords '("c")))
(setq currobj (ssadd (entlast) currobj))
(setq coords (list 
(list 4159.4375 677.0493) 
(list 4085.415 676.6993) 
(list 4085.415 676.5223) 
(list 4159.4375 676.9723)))
(apply 'command (append '("pline") coords '("c")))
(setq currobj (ssadd (entlast) currobj))
(setq coords (list 
(list 4159.4375 676.8293) 
(list 4085.415 676.3793) 
(list 4085.415 676.2023) 
(list 4159.4375 676.7523)))
(apply 'command (append '("pline") coords '("c")))
(setq currobj (ssadd (entlast) currobj))
(setq coords (list 
(list 4159.4375 676.6093) 
(list 4085.415 676.0593) 
(list 4085.415 675.8823) 
(list 4159.4375 676.5323)))
(apply 'command (append '("pline") coords '("c")))
(setq currobj (ssadd (entlast) currobj))
(setq coords (list 
(list 4159.4375 676.3893) 
(list 4085.415 675.7393) 
(list 4085.415 675.5623) 
(list 4159.4375 676.3123)))
(apply 'command (append '("pline") coords '("c")))
(setq currobj (ssadd (entlast) currobj))
(command "_layer" "set" "nitride" "")
(command "_layer" "set" "text" "")
(command "_circle" "4159.0625,665.1693" "0.075")
(command "_circle" "4159.0625,665.4693" "0.075")
(command "_circle" "4159.0625,665.7693" "0.075")
(command "_circle" "4159.0625,666.0693" "0.075")
(command "_circle" "4159.0625,666.3693" "0.075")
(command "_circle" "4158.7625,665.1693" "0.075")
(command "_circle" "4158.7625,665.4693" "0.075")
(command "_circle" "4158.7625,665.7693" "0.075")
(command "_circle" "4158.7625,666.0693" "0.075")
(command "_circle" "4158.7625,666.3693" "0.075")
(command "_circle" "4158.4625,665.1693" "0.075")
(command "_circle" "4158.4625,665.4693" "0.075")
(command "_circle" "4158.4625,665.7693" "0.075")
(command "_circle" "4158.4625,666.0693" "0.075")
(command "_circle" "4158.4625,666.3693" "0.075")
(command "_circle" "4158.1625,665.1693" "0.075")
(command "_circle" "4158.1625,665.4693" "0.075")
(command "_circle" "4158.1625,665.7693" "0.075")
(command "_circle" "4158.1625,666.0693" "0.075")
(command "_circle" "4158.1625,666.3693" "0.075")
(command "_circle" "4157.8625,665.1693" "0.075")
(command "_circle" "4157.8625,665.4693" "0.075")
(command "_circle" "4157.8625,665.7693" "0.075")
(command "_circle" "4157.8625,666.0693" "0.075")
(command "_circle" "4157.8625,666.3693" "0.075")
(command "_layer" "set" "nitride" "")
(setq coords (list 
(list 4160.2625 690.6123) 
(list 4160.2625 806.257) 
(list 4159.7375 806.257) 
(list 4159.7375 690.6123)))
(apply 'command (append '("pline") coords '("c")))
(setq currobj (ssadd (entlast) currobj))
(command "_layer" "set" "prebias" "")
(command "_rectangle" "4159.7375,690.6123" "4160.2625,806.257")
(setq currobj (ssadd (entlast) currobj))
(command "_layer" "set" "nitride" "")
(setq coords (list 
(list 4160.2625 806.257) 
(list 4160.5625 816.257) 
(list 4160.5625 816.257) 
(list 4160.5625 817.257) 
(list 4234.585 816.507) 
(list 4234.585 821.45) 
(list 4160.5625 820.7) 
(list 4160.5625 821.7) 
(list 4160.5625 821.7) 
(list 4160.2625 831.7) 
(list 4159.7375 831.7) 
(list 4159.4375 821.7) 
(list 4159.4375 821.7) 
(list 4159.4375 820.7) 
(list 4085.415 821.45) 
(list 4085.415 816.507) 
(list 4159.4375 817.257) 
(list 4159.4375 816.257) 
(list 4159.4375 816.257) 
(list 4159.7375 806.257)))
(apply 'command (append '("pline") coords '("c")))
(setq currobj (ssadd (entlast) currobj))
(command "_layer" "set" "prebias" "")
(setq coords (list 
(list 4159.4375 806.257) 
(list 4159.4375 817.257) 
(list 4085.415 816.507) 
(list 4085.415 821.45) 
(list 4159.4375 820.7) 
(list 4159.4375 831.7) 
(list 4160.5625 831.7) 
(list 4160.5625 820.7) 
(list 4234.585 821.45) 
(list 4234.585 816.507) 
(list 4160.5625 817.257) 
(list 4160.5625 806.257)))
(apply 'command (append '("pline") coords '("c")))
(setq currobj (ssadd (entlast) currobj))
(command "_layer" "set" "nitride" "")
(command "_layer" "set" "fda1" "")
(setq coords (list 
(list 4160.5625 817.4) 
(list 4234.585 816.65) 
(list 4234.585 816.827) 
(list 4160.5625 817.477)))
(apply 'command (append '("pline") coords '("c")))
(setq currobj (ssadd (entlast) currobj))
(setq coords (list 
(list 4160.5625 817.62) 
(list 4234.585 816.97) 
(list 4234.585 817.147) 
(list 4160.5625 817.697)))
(apply 'command (append '("pline") coords '("c")))
(setq currobj (ssadd (entlast) currobj))
(setq coords (list 
(list 4160.5625 817.84) 
(list 4234.585 817.29) 
(list 4234.585 817.467) 
(list 4160.5625 817.917)))
(apply 'command (append '("pline") coords '("c")))
(setq currobj (ssadd (entlast) currobj))
(setq coords (list 
(list 4160.5625 818.06) 
(list 4234.585 817.61) 
(list 4234.585 817.787) 
(list 4160.5625 818.137)))
(apply 'command (append '("pline") coords '("c")))
(setq currobj (ssadd (entlast) currobj))
(setq coords (list 
(list 4160.5625 818.28) 
(list 4234.585 817.93) 
(list 4234.585 818.107) 
(list 4160.5625 818.357)))
(apply 'command (append '("pline") coords '("c")))
(setq currobj (ssadd (entlast) currobj))
(setq coords (list 
(list 4160.5625 818.5) 
(list 4234.585 818.25) 
(list 4234.585 818.427) 
(list 4160.5625 818.577)))
(apply 'command (append '("pline") coords '("c")))
(setq currobj (ssadd (entlast) currobj))
(setq coords (list 
(list 4160.5625 818.72) 
(list 4234.585 818.57) 
(list 4234.585 818.747) 
(list 4160.5625 818.797)))
(apply 'command (append '("pline") coords '("c")))
(setq currobj (ssadd (entlast) currobj))
(setq coords (list 
(list 4160.5625 818.94) 
(list 4234.585 818.89) 
(list 4234.585 819.067) 
(list 4160.5625 819.017)))
(apply 'command (append '("pline") coords '("c")))
(setq currobj (ssadd (entlast) currobj))
(setq coords (list 
(list 4160.5625 819.16) 
(list 4234.585 819.21) 
(list 4234.585 819.387) 
(list 4160.5625 819.237)))
(apply 'command (append '("pline") coords '("c")))
(setq currobj (ssadd (entlast) currobj))
(setq coords (list 
(list 4160.5625 819.38) 
(list 4234.585 819.53) 
(list 4234.585 819.707) 
(list 4160.5625 819.457)))
(apply 'command (append '("pline") coords '("c")))
(setq currobj (ssadd (entlast) currobj))
(setq coords (list 
(list 4160.5625 819.6) 
(list 4234.585 819.85) 
(list 4234.585 820.027) 
(list 4160.5625 819.677)))
(apply 'command (append '("pline") coords '("c")))
(setq currobj (ssadd (entlast) currobj))
(setq coords (list 
(list 4160.5625 819.82) 
(list 4234.585 820.17) 
(list 4234.585 820.347) 
(list 4160.5625 819.897)))
(apply 'command (append '("pline") coords '("c")))
(setq currobj (ssadd (entlast) currobj))
(setq coords (list 
(list 4160.5625 820.04) 
(list 4234.585 820.49) 
(list 4234.585 820.667) 
(list 4160.5625 820.117)))
(apply 'command (append '("pline") coords '("c")))
(setq currobj (ssadd (entlast) currobj))
(setq coords (list 
(list 4160.5625 820.26) 
(list 4234.585 820.81) 
(list 4234.585 820.987) 
(list 4160.5625 820.337)))
(apply 'command (append '("pline") coords '("c")))
(setq currobj (ssadd (entlast) currobj))
(setq coords (list 
(list 4160.5625 820.48) 
(list 4234.585 821.13) 
(list 4234.585 821.307) 
(list 4160.5625 820.557)))
(apply 'command (append '("pline") coords '("c")))
(setq currobj (ssadd (entlast) currobj))
(setq coords (list 
(list 4159.4375 820.557) 
(list 4085.415 821.307) 
(list 4085.415 821.13) 
(list 4159.4375 820.48)))
(apply 'command (append '("pline") coords '("c")))
(setq currobj (ssadd (entlast) currobj))
(setq coords (list 
(list 4159.4375 820.337) 
(list 4085.415 820.987) 
(list 4085.415 820.81) 
(list 4159.4375 820.26)))
(apply 'command (append '("pline") coords '("c")))
(setq currobj (ssadd (entlast) currobj))
(setq coords (list 
(list 4159.4375 820.117) 
(list 4085.415 820.667) 
(list 4085.415 820.49) 
(list 4159.4375 820.04)))
(apply 'command (append '("pline") coords '("c")))
(setq currobj (ssadd (entlast) currobj))
(setq coords (list 
(list 4159.4375 819.897) 
(list 4085.415 820.347) 
(list 4085.415 820.17) 
(list 4159.4375 819.82)))
(apply 'command (append '("pline") coords '("c")))
(setq currobj (ssadd (entlast) currobj))
(setq coords (list 
(list 4159.4375 819.677) 
(list 4085.415 820.027) 
(list 4085.415 819.85) 
(list 4159.4375 819.6)))
(apply 'command (append '("pline") coords '("c")))
(setq currobj (ssadd (entlast) currobj))
(setq coords (list 
(list 4159.4375 819.457) 
(list 4085.415 819.707) 
(list 4085.415 819.53) 
(list 4159.4375 819.38)))
(apply 'command (append '("pline") coords '("c")))
(setq currobj (ssadd (entlast) currobj))
(setq coords (list 
(list 4159.4375 819.237) 
(list 4085.415 819.387) 
(list 4085.415 819.21) 
(list 4159.4375 819.16)))
(apply 'command (append '("pline") coords '("c")))
(setq currobj (ssadd (entlast) currobj))
(setq coords (list 
(list 4159.4375 819.017) 
(list 4085.415 819.067) 
(list 4085.415 818.89) 
(list 4159.4375 818.94)))
(apply 'command (append '("pline") coords '("c")))
(setq currobj (ssadd (entlast) currobj))
(setq coords (list 
(list 4159.4375 818.797) 
(list 4085.415 818.747) 
(list 4085.415 818.57) 
(list 4159.4375 818.72)))
(apply 'command (append '("pline") coords '("c")))
(setq currobj (ssadd (entlast) currobj))
(setq coords (list 
(list 4159.4375 818.577) 
(list 4085.415 818.427) 
(list 4085.415 818.25) 
(list 4159.4375 818.5)))
(apply 'command (append '("pline") coords '("c")))
(setq currobj (ssadd (entlast) currobj))
(setq coords (list 
(list 4159.4375 818.357) 
(list 4085.415 818.107) 
(list 4085.415 817.93) 
(list 4159.4375 818.28)))
(apply 'command (append '("pline") coords '("c")))
(setq currobj (ssadd (entlast) currobj))
(setq coords (list 
(list 4159.4375 818.137) 
(list 4085.415 817.787) 
(list 4085.415 817.61) 
(list 4159.4375 818.06)))
(apply 'command (append '("pline") coords '("c")))
(setq currobj (ssadd (entlast) currobj))
(setq coords (list 
(list 4159.4375 817.917) 
(list 4085.415 817.467) 
(list 4085.415 817.29) 
(list 4159.4375 817.84)))
(apply 'command (append '("pline") coords '("c")))
(setq currobj (ssadd (entlast) currobj))
(setq coords (list 
(list 4159.4375 817.697) 
(list 4085.415 817.147) 
(list 4085.415 816.97) 
(list 4159.4375 817.62)))
(apply 'command (append '("pline") coords '("c")))
(setq currobj (ssadd (entlast) currobj))
(setq coords (list 
(list 4159.4375 817.477) 
(list 4085.415 816.827) 
(list 4085.415 816.65) 
(list 4159.4375 817.4)))
(apply 'command (append '("pline") coords '("c")))
(setq currobj (ssadd (entlast) currobj))
(command "_layer" "set" "nitride" "")
(command "_layer" "set" "text" "")
(command "_circle" "4159.0625,806.257" "0.075")
(command "_circle" "4159.0625,806.557" "0.075")
(command "_circle" "4159.0625,806.857" "0.075")
(command "_circle" "4159.0625,807.157" "0.075")
(command "_circle" "4159.0625,807.457" "0.075")
(command "_circle" "4158.7625,806.257" "0.075")
(command "_circle" "4158.7625,806.557" "0.075")
(command "_circle" "4158.7625,806.857" "0.075")
(command "_circle" "4158.7625,807.157" "0.075")
(command "_circle" "4158.7625,807.457" "0.075")
(command "_circle" "4158.4625,806.257" "0.075")
(command "_circle" "4158.4625,806.557" "0.075")
(command "_circle" "4158.4625,806.857" "0.075")
(command "_circle" "4158.4625,807.157" "0.075")
(command "_circle" "4158.4625,807.457" "0.075")
(command "_circle" "4158.1625,806.257" "0.075")
(command "_circle" "4158.1625,806.557" "0.075")
(command "_circle" "4158.1625,806.857" "0.075")
(command "_circle" "4158.1625,807.157" "0.075")
(command "_circle" "4158.1625,807.457" "0.075")
(command "_circle" "4157.8625,806.257" "0.075")
(command "_circle" "4157.8625,806.557" "0.075")
(command "_circle" "4157.8625,806.857" "0.075")
(command "_circle" "4157.8625,807.157" "0.075")
(command "_circle" "4157.8625,807.457" "0.075")
(command "_layer" "set" "nitride" "")
(setq coords (list 
(list 4160.2625 831.7) 
(list 4160.2625 836.7) 
(list 4159.7375 836.7) 
(list 4159.7375 831.7)))
(apply 'command (append '("pline") coords '("c")))
(setq currobj (ssadd (entlast) currobj))
(command "_layer" "set" "prebias" "")
(command "_rectangle" "4159.7375,831.7" "4160.2625,836.7")
(setq currobj (ssadd (entlast) currobj))
(command "_layer" "set" "nitride" "")
(setq cooledsinglenanobeam13 currobj)
(setq currobj nil)
(setq currobj (ssadd))
; DRAWING PHOTONIC CRYSTAL
(command "_layer" "set" "negYjunc" "")
(setq coords (list 
(list 4160.135 866.7) 
(list 4160 851.7) 
(list 4160 866.7)))
(apply 'command (append '("pline") coords '("c")))
(setq currobj (ssadd (entlast) currobj))
(setq coords (list 
(list 4160.2625 836.7) 
(list 4160.415 866.7) 
(list 4161.134 866.7) 
(list 4161.134 836.7)))
(apply 'command (append '("pline") coords '("c")))
(setq currobj (ssadd (entlast) currobj))
(setq coords (list 
(list 4159.865 866.7) 
(list 4160 851.7) 
(list 4160 866.7)))
(apply 'command (append '("pline") coords '("c")))
(setq currobj (ssadd (entlast) currobj))
(setq coords (list 
(list 4159.7375 836.7) 
(list 4159.585 866.7) 
(list 4158.866 866.7) 
(list 4158.866 836.7)))
(apply 'command (append '("pline") coords '("c")))
(setq currobj (ssadd (entlast) currobj))
(command "_layer" "set" "nitride" "")
(setq yjunction13 currobj)
(setq currobj nil)
(setq currobj (ssadd))
(setq tap13 nil)
(setq tap13 (ssadd))
(command "_layer" "set" "phc" "")
(setq coords (list 
(list 4160 866.7) 
(list 4160.135 866.7) 
(list 4160.135 866.7103) 
(list 4160.135 866.7206) 
(list 4160.135 866.7308) 
(list 4160.135 866.7411) 
(list 4160.135 866.7514) 
(list 4160.135 866.7617) 
(list 4160.135 866.7719) 
(list 4160.135 866.7822) 
(list 4160.135 866.7925) 
(list 4160.135 866.8028) 
(list 4160.135 866.8131) 
(list 4160.135 866.8233) 
(list 4160.135 866.8336) 
(list 4160.135 866.8439) 
(list 4160.135 866.8542) 
(list 4160.135 866.8644) 
(list 4160.135 866.8747) 
(list 4160.135 866.885) 
(list 4160.135 866.8953) 
(list 4160.135 866.9056) 
(list 4160.135 866.9158) 
(list 4160.135 866.9261) 
(list 4160.135 866.9364) 
(list 4160.135 866.9467) 
(list 4160.135 866.9569) 
(list 4160.135 866.9672) 
(list 4160.135 866.9775) 
(list 4160.135 866.9878) 
(list 4160.135 866.9981) 
(list 4160.135 867.0083) 
(list 4160.135 867.0186) 
(list 4160.135 867.0289) 
(list 4160.135 867.0392) 
(list 4160.135 867.0494) 
(list 4160.135 867.0597) 
(list 4160.135 867.07) 
(list 4160 867.07)))
(apply 'command (append '("pline") coords '("c")))
(setq tap13 (ssadd (entlast) tap13))
(command "_mirror" (entlast) "" "4160,900" "4160,901" "No")
(setq tap13 (ssadd (entlast) tap13))
(setq coords (list 
(list 4160.4251 866.7) 
(list 4160.415 866.7) 
(list 4160.4153 866.7103) 
(list 4160.4155 866.7206) 
(list 4160.4157 866.7308) 
(list 4160.4159 866.7411) 
(list 4160.416 866.7514) 
(list 4160.4159 866.7617) 
(list 4160.4158 866.7719) 
(list 4160.4156 866.7822) 
(list 4160.4153 866.7925) 
(list 4160.4149 866.8028) 
(list 4160.4144 866.8131) 
(list 4160.4139 866.8233) 
(list 4160.4134 866.8336) 
(list 4160.4128 866.8439) 
(list 4160.4123 866.8542) 
(list 4160.4118 866.8644) 
(list 4160.4114 866.8747) 
(list 4160.4111 866.885) 
(list 4160.411 866.8953) 
(list 4160.411 866.9056) 
(list 4160.4112 866.9158) 
(list 4160.4116 866.9261) 
(list 4160.4121 866.9364) 
(list 4160.4128 866.9467) 
(list 4160.4137 866.9569) 
(list 4160.4147 866.9672) 
(list 4160.4159 866.9775) 
(list 4160.4171 866.9878) 
(list 4160.4184 866.9981) 
(list 4160.4197 867.0083) 
(list 4160.421 867.0186) 
(list 4160.4222 867.0289) 
(list 4160.4232 867.0392) 
(list 4160.4241 867.0494) 
(list 4160.4247 867.0597) 
(list 4160.4251 867.07) 
(list 4160.4251 867.07)))
(apply 'command (append '("pline") coords '("c")))
(setq tap13 (ssadd (entlast) tap13))
(command "_mirror" (entlast) "" "4160,900" "4160,901" "No")
(setq tap13 (ssadd (entlast) tap13))
(setq coords (list 
(list 4161.134 866.7) 
(list 4160.4251 866.7) 
(list 4160.4251 866.7103) 
(list 4160.4251 866.7206) 
(list 4160.4251 866.7308) 
(list 4160.4251 866.7411) 
(list 4160.4251 866.7514) 
(list 4160.4251 866.7617) 
(list 4160.4251 866.7719) 
(list 4160.4251 866.7822) 
(list 4160.4251 866.7925) 
(list 4160.4251 866.8028) 
(list 4160.4251 866.8131) 
(list 4160.4251 866.8233) 
(list 4160.4251 866.8336) 
(list 4160.4251 866.8439) 
(list 4160.4251 866.8542) 
(list 4160.4251 866.8644) 
(list 4160.4251 866.8747) 
(list 4160.4251 866.885) 
(list 4160.4251 866.8953) 
(list 4160.4251 866.9056) 
(list 4160.4251 866.9158) 
(list 4160.4251 866.9261) 
(list 4160.4251 866.9364) 
(list 4160.4251 866.9467) 
(list 4160.4251 866.9569) 
(list 4160.4251 866.9672) 
(list 4160.4251 866.9775) 
(list 4160.4251 866.9878) 
(list 4160.4251 866.9981) 
(list 4160.4251 867.0083) 
(list 4160.4251 867.0186) 
(list 4160.4251 867.0289) 
(list 4160.4251 867.0392) 
(list 4160.4251 867.0494) 
(list 4160.4251 867.0597) 
(list 4160.4251 867.07) 
(list 4161.134 867.07)))
(apply 'command (append '("pline") coords '("c")))
(setq tap13 (ssadd (entlast) tap13))
(command "_mirror" (entlast) "" "4160,900" "4160,901" "No")
(setq tap13 (ssadd (entlast) tap13))
(setq coords (list 
(list 4160 867.07) 
(list 4160.135 867.07) 
(list 4160.135 867.0803) 
(list 4160.135 867.0906) 
(list 4160.135 867.1008) 
(list 4160.135 867.1111) 
(list 4160.135 867.1214) 
(list 4160.135 867.1317) 
(list 4160.135 867.1419) 
(list 4160.135 867.1522) 
(list 4160.135 867.1625) 
(list 4160.135 867.1728) 
(list 4160.135 867.1831) 
(list 4160.135 867.1933) 
(list 4160.135 867.2036) 
(list 4160.135 867.2139) 
(list 4160.135 867.2242) 
(list 4160.135 867.2344) 
(list 4160.135 867.2447) 
(list 4160.135 867.255) 
(list 4160.135 867.2653) 
(list 4160.135 867.2756) 
(list 4160.135 867.2858) 
(list 4160.135 867.2961) 
(list 4160.135 867.3064) 
(list 4160.135 867.3167) 
(list 4160.135 867.3269) 
(list 4160.135 867.3372) 
(list 4160.135 867.3475) 
(list 4160.135 867.3578) 
(list 4160.135 867.3681) 
(list 4160.135 867.3783) 
(list 4160.135 867.3886) 
(list 4160.135 867.3989) 
(list 4160.135 867.4092) 
(list 4160.135 867.4194) 
(list 4160.135 867.4297) 
(list 4160.135 867.44) 
(list 4160 867.44)))
(apply 'command (append '("pline") coords '("c")))
(setq tap13 (ssadd (entlast) tap13))
(command "_mirror" (entlast) "" "4160,900" "4160,901" "No")
(setq tap13 (ssadd (entlast) tap13))
(setq coords (list 
(list 4160.4353 867.07) 
(list 4160.4251 867.07) 
(list 4160.4253 867.0803) 
(list 4160.4251 867.0906) 
(list 4160.4247 867.1008) 
(list 4160.4239 867.1111) 
(list 4160.4229 867.1214) 
(list 4160.4216 867.1317) 
(list 4160.4201 867.1419) 
(list 4160.4184 867.1522) 
(list 4160.4165 867.1625) 
(list 4160.4146 867.1728) 
(list 4160.4126 867.1831) 
(list 4160.4106 867.1933) 
(list 4160.4088 867.2036) 
(list 4160.4072 867.2139) 
(list 4160.4057 867.2242) 
(list 4160.4046 867.2344) 
(list 4160.4038 867.2447) 
(list 4160.4034 867.255) 
(list 4160.4034 867.2653) 
(list 4160.4038 867.2756) 
(list 4160.4047 867.2858) 
(list 4160.4059 867.2961) 
(list 4160.4076 867.3064) 
(list 4160.4096 867.3167) 
(list 4160.4119 867.3269) 
(list 4160.4144 867.3372) 
(list 4160.4171 867.3475) 
(list 4160.4199 867.3578) 
(list 4160.4227 867.3681) 
(list 4160.4254 867.3783) 
(list 4160.4279 867.3886) 
(list 4160.4302 867.3989) 
(list 4160.4321 867.4092) 
(list 4160.4337 867.4194) 
(list 4160.4347 867.4297) 
(list 4160.4353 867.44) 
(list 4160.4353 867.44)))
(apply 'command (append '("pline") coords '("c")))
(setq tap13 (ssadd (entlast) tap13))
(command "_mirror" (entlast) "" "4160,900" "4160,901" "No")
(setq tap13 (ssadd (entlast) tap13))
(setq coords (list 
(list 4161.134 867.07) 
(list 4160.4353 867.07) 
(list 4160.4353 867.0803) 
(list 4160.4353 867.0906) 
(list 4160.4353 867.1008) 
(list 4160.4353 867.1111) 
(list 4160.4353 867.1214) 
(list 4160.4353 867.1317) 
(list 4160.4353 867.1419) 
(list 4160.4353 867.1522) 
(list 4160.4353 867.1625) 
(list 4160.4353 867.1728) 
(list 4160.4353 867.1831) 
(list 4160.4353 867.1933) 
(list 4160.4353 867.2036) 
(list 4160.4353 867.2139) 
(list 4160.4353 867.2242) 
(list 4160.4353 867.2344) 
(list 4160.4353 867.2447) 
(list 4160.4353 867.255) 
(list 4160.4353 867.2653) 
(list 4160.4353 867.2756) 
(list 4160.4353 867.2858) 
(list 4160.4353 867.2961) 
(list 4160.4353 867.3064) 
(list 4160.4353 867.3167) 
(list 4160.4353 867.3269) 
(list 4160.4353 867.3372) 
(list 4160.4353 867.3475) 
(list 4160.4353 867.3578) 
(list 4160.4353 867.3681) 
(list 4160.4353 867.3783) 
(list 4160.4353 867.3886) 
(list 4160.4353 867.3989) 
(list 4160.4353 867.4092) 
(list 4160.4353 867.4194) 
(list 4160.4353 867.4297) 
(list 4160.4353 867.44) 
(list 4161.134 867.44)))
(apply 'command (append '("pline") coords '("c")))
(setq tap13 (ssadd (entlast) tap13))
(command "_mirror" (entlast) "" "4160,900" "4160,901" "No")
(setq tap13 (ssadd (entlast) tap13))
(setq coords (list 
(list 4160 867.44) 
(list 4160.135 867.44) 
(list 4160.135 867.4503) 
(list 4160.135 867.4606) 
(list 4160.135 867.4708) 
(list 4160.135 867.4811) 
(list 4160.135 867.4914) 
(list 4160.135 867.5017) 
(list 4160.135 867.5119) 
(list 4160.135 867.5222) 
(list 4160.135 867.5325) 
(list 4160.135 867.5428) 
(list 4160.135 867.5531) 
(list 4160.135 867.5633) 
(list 4160.135 867.5736) 
(list 4160.135 867.5839) 
(list 4160.135 867.5942) 
(list 4160.135 867.6044) 
(list 4160.135 867.6147) 
(list 4160.135 867.625) 
(list 4160.135 867.6353) 
(list 4160.135 867.6456) 
(list 4160.135 867.6558) 
(list 4160.135 867.6661) 
(list 4160.135 867.6764) 
(list 4160.135 867.6867) 
(list 4160.135 867.6969) 
(list 4160.135 867.7072) 
(list 4160.135 867.7175) 
(list 4160.135 867.7278) 
(list 4160.135 867.7381) 
(list 4160.135 867.7483) 
(list 4160.135 867.7586) 
(list 4160.135 867.7689) 
(list 4160.135 867.7792) 
(list 4160.135 867.7894) 
(list 4160.135 867.7997) 
(list 4160.135 867.81) 
(list 4160 867.81)))
(apply 'command (append '("pline") coords '("c")))
(setq tap13 (ssadd (entlast) tap13))
(command "_mirror" (entlast) "" "4160,900" "4160,901" "No")
(setq tap13 (ssadd (entlast) tap13))
(setq coords (list 
(list 4160.4454 867.44) 
(list 4160.4353 867.44) 
(list 4160.4353 867.4503) 
(list 4160.4347 867.4606) 
(list 4160.4336 867.4708) 
(list 4160.432 867.4811) 
(list 4160.4298 867.4914) 
(list 4160.4273 867.5017) 
(list 4160.4243 867.5119) 
(list 4160.4211 867.5222) 
(list 4160.4177 867.5325) 
(list 4160.4142 867.5428) 
(list 4160.4107 867.5531) 
(list 4160.4074 867.5633) 
(list 4160.4043 867.5736) 
(list 4160.4015 867.5839) 
(list 4160.3992 867.5942) 
(list 4160.3974 867.6044) 
(list 4160.3962 867.6147) 
(list 4160.3957 867.625) 
(list 4160.3958 867.6353) 
(list 4160.3966 867.6456) 
(list 4160.3981 867.6558) 
(list 4160.4003 867.6661) 
(list 4160.403 867.6764) 
(list 4160.4063 867.6867) 
(list 4160.41 867.6969) 
(list 4160.414 867.7072) 
(list 4160.4183 867.7175) 
(list 4160.4226 867.7278) 
(list 4160.4269 867.7381) 
(list 4160.4311 867.7483) 
(list 4160.4349 867.7586) 
(list 4160.4382 867.7689) 
(list 4160.4411 867.7792) 
(list 4160.4433 867.7894) 
(list 4160.4447 867.7997) 
(list 4160.4454 867.81) 
(list 4160.4454 867.81)))
(apply 'command (append '("pline") coords '("c")))
(setq tap13 (ssadd (entlast) tap13))
(command "_mirror" (entlast) "" "4160,900" "4160,901" "No")
(setq tap13 (ssadd (entlast) tap13))
(setq coords (list 
(list 4161.134 867.44) 
(list 4160.4454 867.44) 
(list 4160.4454 867.4503) 
(list 4160.4454 867.4606) 
(list 4160.4454 867.4708) 
(list 4160.4454 867.4811) 
(list 4160.4454 867.4914) 
(list 4160.4454 867.5017) 
(list 4160.4454 867.5119) 
(list 4160.4454 867.5222) 
(list 4160.4454 867.5325) 
(list 4160.4454 867.5428) 
(list 4160.4454 867.5531) 
(list 4160.4454 867.5633) 
(list 4160.4454 867.5736) 
(list 4160.4454 867.5839) 
(list 4160.4454 867.5942) 
(list 4160.4454 867.6044) 
(list 4160.4454 867.6147) 
(list 4160.4454 867.625) 
(list 4160.4454 867.6353) 
(list 4160.4454 867.6456) 
(list 4160.4454 867.6558) 
(list 4160.4454 867.6661) 
(list 4160.4454 867.6764) 
(list 4160.4454 867.6867) 
(list 4160.4454 867.6969) 
(list 4160.4454 867.7072) 
(list 4160.4454 867.7175) 
(list 4160.4454 867.7278) 
(list 4160.4454 867.7381) 
(list 4160.4454 867.7483) 
(list 4160.4454 867.7586) 
(list 4160.4454 867.7689) 
(list 4160.4454 867.7792) 
(list 4160.4454 867.7894) 
(list 4160.4454 867.7997) 
(list 4160.4454 867.81) 
(list 4161.134 867.81)))
(apply 'command (append '("pline") coords '("c")))
(setq tap13 (ssadd (entlast) tap13))
(command "_mirror" (entlast) "" "4160,900" "4160,901" "No")
(setq tap13 (ssadd (entlast) tap13))
(setq coords (list 
(list 4160 867.81) 
(list 4160.135 867.81) 
(list 4160.135 867.8203) 
(list 4160.135 867.8306) 
(list 4160.135 867.8408) 
(list 4160.135 867.8511) 
(list 4160.135 867.8614) 
(list 4160.135 867.8717) 
(list 4160.135 867.8819) 
(list 4160.135 867.8922) 
(list 4160.135 867.9025) 
(list 4160.135 867.9128) 
(list 4160.135 867.9231) 
(list 4160.135 867.9333) 
(list 4160.135 867.9436) 
(list 4160.135 867.9539) 
(list 4160.135 867.9642) 
(list 4160.135 867.9744) 
(list 4160.135 867.9847) 
(list 4160.135 867.995) 
(list 4160.135 868.0053) 
(list 4160.135 868.0156) 
(list 4160.135 868.0258) 
(list 4160.135 868.0361) 
(list 4160.135 868.0464) 
(list 4160.135 868.0567) 
(list 4160.135 868.0669) 
(list 4160.135 868.0772) 
(list 4160.135 868.0875) 
(list 4160.135 868.0978) 
(list 4160.135 868.1081) 
(list 4160.135 868.1183) 
(list 4160.135 868.1286) 
(list 4160.135 868.1389) 
(list 4160.135 868.1492) 
(list 4160.135 868.1594) 
(list 4160.135 868.1697) 
(list 4160.135 868.18) 
(list 4160 868.18)))
(apply 'command (append '("pline") coords '("c")))
(setq tap13 (ssadd (entlast) tap13))
(command "_mirror" (entlast) "" "4160,900" "4160,901" "No")
(setq tap13 (ssadd (entlast) tap13))
(setq coords (list 
(list 4160.4555 867.81) 
(list 4160.4454 867.81) 
(list 4160.4453 867.8203) 
(list 4160.4443 867.8306) 
(list 4160.4426 867.8408) 
(list 4160.44 867.8511) 
(list 4160.4368 867.8614) 
(list 4160.4329 867.8717) 
(list 4160.4286 867.8819) 
(list 4160.4239 867.8922) 
(list 4160.4189 867.9025) 
(list 4160.4138 867.9128) 
(list 4160.4089 867.9231) 
(list 4160.4041 867.9333) 
(list 4160.3997 867.9436) 
(list 4160.3959 867.9539) 
(list 4160.3927 867.9642) 
(list 4160.3902 867.9744) 
(list 4160.3886 867.9847) 
(list 4160.3879 867.995) 
(list 4160.3882 868.0053) 
(list 4160.3894 868.0156) 
(list 4160.3916 868.0258) 
(list 4160.3946 868.0361) 
(list 4160.3985 868.0464) 
(list 4160.403 868.0567) 
(list 4160.4081 868.0669) 
(list 4160.4137 868.0772) 
(list 4160.4195 868.0875) 
(list 4160.4254 868.0978) 
(list 4160.4312 868.1081) 
(list 4160.4367 868.1183) 
(list 4160.4418 868.1286) 
(list 4160.4463 868.1389) 
(list 4160.45 868.1492) 
(list 4160.4528 868.1594) 
(list 4160.4547 868.1697) 
(list 4160.4555 868.18) 
(list 4160.4555 868.18)))
(apply 'command (append '("pline") coords '("c")))
(setq tap13 (ssadd (entlast) tap13))
(command "_mirror" (entlast) "" "4160,900" "4160,901" "No")
(setq tap13 (ssadd (entlast) tap13))
(setq coords (list 
(list 4161.134 867.81) 
(list 4160.4555 867.81) 
(list 4160.4555 867.8203) 
(list 4160.4555 867.8306) 
(list 4160.4555 867.8408) 
(list 4160.4555 867.8511) 
(list 4160.4555 867.8614) 
(list 4160.4555 867.8717) 
(list 4160.4555 867.8819) 
(list 4160.4555 867.8922) 
(list 4160.4555 867.9025) 
(list 4160.4555 867.9128) 
(list 4160.4555 867.9231) 
(list 4160.4555 867.9333) 
(list 4160.4555 867.9436) 
(list 4160.4555 867.9539) 
(list 4160.4555 867.9642) 
(list 4160.4555 867.9744) 
(list 4160.4555 867.9847) 
(list 4160.4555 867.995) 
(list 4160.4555 868.0053) 
(list 4160.4555 868.0156) 
(list 4160.4555 868.0258) 
(list 4160.4555 868.0361) 
(list 4160.4555 868.0464) 
(list 4160.4555 868.0567) 
(list 4160.4555 868.0669) 
(list 4160.4555 868.0772) 
(list 4160.4555 868.0875) 
(list 4160.4555 868.0978) 
(list 4160.4555 868.1081) 
(list 4160.4555 868.1183) 
(list 4160.4555 868.1286) 
(list 4160.4555 868.1389) 
(list 4160.4555 868.1492) 
(list 4160.4555 868.1594) 
(list 4160.4555 868.1697) 
(list 4160.4555 868.18) 
(list 4161.134 868.18)))
(apply 'command (append '("pline") coords '("c")))
(setq tap13 (ssadd (entlast) tap13))
(command "_mirror" (entlast) "" "4160,900" "4160,901" "No")
(setq tap13 (ssadd (entlast) tap13))
(setq coords (list 
(list 4160 868.18) 
(list 4160.135 868.18) 
(list 4160.135 868.1903) 
(list 4160.135 868.2006) 
(list 4160.135 868.2108) 
(list 4160.135 868.2211) 
(list 4160.135 868.2314) 
(list 4160.135 868.2417) 
(list 4160.135 868.2519) 
(list 4160.135 868.2622) 
(list 4160.135 868.2725) 
(list 4160.135 868.2828) 
(list 4160.135 868.2931) 
(list 4160.135 868.3033) 
(list 4160.135 868.3136) 
(list 4160.135 868.3239) 
(list 4160.135 868.3342) 
(list 4160.135 868.3444) 
(list 4160.135 868.3547) 
(list 4160.135 868.365) 
(list 4160.135 868.3753) 
(list 4160.135 868.3856) 
(list 4160.135 868.3958) 
(list 4160.135 868.4061) 
(list 4160.135 868.4164) 
(list 4160.135 868.4267) 
(list 4160.135 868.4369) 
(list 4160.135 868.4472) 
(list 4160.135 868.4575) 
(list 4160.135 868.4678) 
(list 4160.135 868.4781) 
(list 4160.135 868.4883) 
(list 4160.135 868.4986) 
(list 4160.135 868.5089) 
(list 4160.135 868.5192) 
(list 4160.135 868.5294) 
(list 4160.135 868.5397) 
(list 4160.135 868.55) 
(list 4160 868.55)))
(apply 'command (append '("pline") coords '("c")))
(setq tap13 (ssadd (entlast) tap13))
(command "_mirror" (entlast) "" "4160,900" "4160,901" "No")
(setq tap13 (ssadd (entlast) tap13))
(setq coords (list 
(list 4160.4657 868.18) 
(list 4160.4555 868.18) 
(list 4160.4553 868.1903) 
(list 4160.4539 868.2006) 
(list 4160.4515 868.2108) 
(list 4160.4481 868.2211) 
(list 4160.4437 868.2314) 
(list 4160.4386 868.2417) 
(list 4160.4328 868.2519) 
(list 4160.4266 868.2622) 
(list 4160.4201 868.2725) 
(list 4160.4135 868.2828) 
(list 4160.407 868.2931) 
(list 4160.4008 868.3033) 
(list 4160.3952 868.3136) 
(list 4160.3902 868.3239) 
(list 4160.3861 868.3342) 
(list 4160.383 868.3444) 
(list 4160.381 868.3547) 
(list 4160.3802 868.365) 
(list 4160.3806 868.3753) 
(list 4160.3822 868.3856) 
(list 4160.385 868.3958) 
(list 4160.389 868.4061) 
(list 4160.3939 868.4164) 
(list 4160.3998 868.4267) 
(list 4160.4063 868.4369) 
(list 4160.4133 868.4472) 
(list 4160.4207 868.4575) 
(list 4160.4281 868.4678) 
(list 4160.4354 868.4781) 
(list 4160.4424 868.4883) 
(list 4160.4487 868.4986) 
(list 4160.4543 868.5089) 
(list 4160.4589 868.5192) 
(list 4160.4624 868.5294) 
(list 4160.4647 868.5397) 
(list 4160.4657 868.55) 
(list 4160.4657 868.55)))
(apply 'command (append '("pline") coords '("c")))
(setq tap13 (ssadd (entlast) tap13))
(command "_mirror" (entlast) "" "4160,900" "4160,901" "No")
(setq tap13 (ssadd (entlast) tap13))
(setq coords (list 
(list 4161.134 868.18) 
(list 4160.4657 868.18) 
(list 4160.4657 868.1903) 
(list 4160.4657 868.2006) 
(list 4160.4657 868.2108) 
(list 4160.4657 868.2211) 
(list 4160.4657 868.2314) 
(list 4160.4657 868.2417) 
(list 4160.4657 868.2519) 
(list 4160.4657 868.2622) 
(list 4160.4657 868.2725) 
(list 4160.4657 868.2828) 
(list 4160.4657 868.2931) 
(list 4160.4657 868.3033) 
(list 4160.4657 868.3136) 
(list 4160.4657 868.3239) 
(list 4160.4657 868.3342) 
(list 4160.4657 868.3444) 
(list 4160.4657 868.3547) 
(list 4160.4657 868.365) 
(list 4160.4657 868.3753) 
(list 4160.4657 868.3856) 
(list 4160.4657 868.3958) 
(list 4160.4657 868.4061) 
(list 4160.4657 868.4164) 
(list 4160.4657 868.4267) 
(list 4160.4657 868.4369) 
(list 4160.4657 868.4472) 
(list 4160.4657 868.4575) 
(list 4160.4657 868.4678) 
(list 4160.4657 868.4781) 
(list 4160.4657 868.4883) 
(list 4160.4657 868.4986) 
(list 4160.4657 868.5089) 
(list 4160.4657 868.5192) 
(list 4160.4657 868.5294) 
(list 4160.4657 868.5397) 
(list 4160.4657 868.55) 
(list 4161.134 868.55)))
(apply 'command (append '("pline") coords '("c")))
(setq tap13 (ssadd (entlast) tap13))
(command "_mirror" (entlast) "" "4160,900" "4160,901" "No")
(setq tap13 (ssadd (entlast) tap13))
(setq coords (list 
(list 4160 868.55) 
(list 4160.135 868.55) 
(list 4160.135 868.5603) 
(list 4160.135 868.5706) 
(list 4160.135 868.5808) 
(list 4160.135 868.5911) 
(list 4160.135 868.6014) 
(list 4160.135 868.6117) 
(list 4160.135 868.6219) 
(list 4160.135 868.6322) 
(list 4160.135 868.6425) 
(list 4160.135 868.6528) 
(list 4160.135 868.6631) 
(list 4160.135 868.6733) 
(list 4160.135 868.6836) 
(list 4160.135 868.6939) 
(list 4160.135 868.7042) 
(list 4160.135 868.7144) 
(list 4160.135 868.7247) 
(list 4160.135 868.735) 
(list 4160.135 868.7453) 
(list 4160.135 868.7556) 
(list 4160.135 868.7658) 
(list 4160.135 868.7761) 
(list 4160.135 868.7864) 
(list 4160.135 868.7967) 
(list 4160.135 868.8069) 
(list 4160.135 868.8172) 
(list 4160.135 868.8275) 
(list 4160.135 868.8378) 
(list 4160.135 868.8481) 
(list 4160.135 868.8583) 
(list 4160.135 868.8686) 
(list 4160.135 868.8789) 
(list 4160.135 868.8892) 
(list 4160.135 868.8994) 
(list 4160.135 868.9097) 
(list 4160.135 868.92) 
(list 4160 868.92)))
(apply 'command (append '("pline") coords '("c")))
(setq tap13 (ssadd (entlast) tap13))
(command "_mirror" (entlast) "" "4160,900" "4160,901" "No")
(setq tap13 (ssadd (entlast) tap13))
(setq coords (list 
(list 4160.4758 868.55) 
(list 4160.4657 868.55) 
(list 4160.4653 868.5603) 
(list 4160.4635 868.5706) 
(list 4160.4604 868.5808) 
(list 4160.4561 868.5911) 
(list 4160.4507 868.6014) 
(list 4160.4443 868.6117) 
(list 4160.4371 868.6219) 
(list 4160.4294 868.6322) 
(list 4160.4213 868.6425) 
(list 4160.4131 868.6528) 
(list 4160.4052 868.6631) 
(list 4160.3976 868.6733) 
(list 4160.3906 868.6836) 
(list 4160.3846 868.6939) 
(list 4160.3796 868.7042) 
(list 4160.3758 868.7144) 
(list 4160.3734 868.7247) 
(list 4160.3725 868.735) 
(list 4160.373 868.7453) 
(list 4160.375 868.7556) 
(list 4160.3785 868.7658) 
(list 4160.3833 868.7761) 
(list 4160.3894 868.7864) 
(list 4160.3965 868.7967) 
(list 4160.4044 868.8069) 
(list 4160.413 868.8172) 
(list 4160.4219 868.8275) 
(list 4160.4309 868.8378) 
(list 4160.4397 868.8481) 
(list 4160.4481 868.8583) 
(list 4160.4557 868.8686) 
(list 4160.4624 868.8789) 
(list 4160.4679 868.8892) 
(list 4160.472 868.8994) 
(list 4160.4747 868.9097) 
(list 4160.4758 868.92) 
(list 4160.4758 868.92)))
(apply 'command (append '("pline") coords '("c")))
(setq tap13 (ssadd (entlast) tap13))
(command "_mirror" (entlast) "" "4160,900" "4160,901" "No")
(setq tap13 (ssadd (entlast) tap13))
(setq coords (list 
(list 4161.134 868.55) 
(list 4160.4758 868.55) 
(list 4160.4758 868.5603) 
(list 4160.4758 868.5706) 
(list 4160.4758 868.5808) 
(list 4160.4758 868.5911) 
(list 4160.4758 868.6014) 
(list 4160.4758 868.6117) 
(list 4160.4758 868.6219) 
(list 4160.4758 868.6322) 
(list 4160.4758 868.6425) 
(list 4160.4758 868.6528) 
(list 4160.4758 868.6631) 
(list 4160.4758 868.6733) 
(list 4160.4758 868.6836) 
(list 4160.4758 868.6939) 
(list 4160.4758 868.7042) 
(list 4160.4758 868.7144) 
(list 4160.4758 868.7247) 
(list 4160.4758 868.735) 
(list 4160.4758 868.7453) 
(list 4160.4758 868.7556) 
(list 4160.4758 868.7658) 
(list 4160.4758 868.7761) 
(list 4160.4758 868.7864) 
(list 4160.4758 868.7967) 
(list 4160.4758 868.8069) 
(list 4160.4758 868.8172) 
(list 4160.4758 868.8275) 
(list 4160.4758 868.8378) 
(list 4160.4758 868.8481) 
(list 4160.4758 868.8583) 
(list 4160.4758 868.8686) 
(list 4160.4758 868.8789) 
(list 4160.4758 868.8892) 
(list 4160.4758 868.8994) 
(list 4160.4758 868.9097) 
(list 4160.4758 868.92) 
(list 4161.134 868.92)))
(apply 'command (append '("pline") coords '("c")))
(setq tap13 (ssadd (entlast) tap13))
(command "_mirror" (entlast) "" "4160,900" "4160,901" "No")
(setq tap13 (ssadd (entlast) tap13))
(setq coords (list 
(list 4160 868.92) 
(list 4160.135 868.92) 
(list 4160.135 868.9303) 
(list 4160.135 868.9406) 
(list 4160.135 868.9508) 
(list 4160.135 868.9611) 
(list 4160.135 868.9714) 
(list 4160.135 868.9817) 
(list 4160.135 868.9919) 
(list 4160.135 869.0022) 
(list 4160.135 869.0125) 
(list 4160.135 869.0228) 
(list 4160.135 869.0331) 
(list 4160.135 869.0433) 
(list 4160.135 869.0536) 
(list 4160.135 869.0639) 
(list 4160.135 869.0742) 
(list 4160.135 869.0844) 
(list 4160.135 869.0947) 
(list 4160.135 869.105) 
(list 4160.135 869.1153) 
(list 4160.135 869.1256) 
(list 4160.135 869.1358) 
(list 4160.135 869.1461) 
(list 4160.135 869.1564) 
(list 4160.135 869.1667) 
(list 4160.135 869.1769) 
(list 4160.135 869.1872) 
(list 4160.135 869.1975) 
(list 4160.135 869.2078) 
(list 4160.135 869.2181) 
(list 4160.135 869.2283) 
(list 4160.135 869.2386) 
(list 4160.135 869.2489) 
(list 4160.135 869.2592) 
(list 4160.135 869.2694) 
(list 4160.135 869.2797) 
(list 4160.135 869.29) 
(list 4160 869.29)))
(apply 'command (append '("pline") coords '("c")))
(setq tap13 (ssadd (entlast) tap13))
(command "_mirror" (entlast) "" "4160,900" "4160,901" "No")
(setq tap13 (ssadd (entlast) tap13))
(setq coords (list 
(list 4160.4859 868.92) 
(list 4160.4758 868.92) 
(list 4160.4753 868.9303) 
(list 4160.4731 868.9406) 
(list 4160.4694 868.9508) 
(list 4160.4642 868.9611) 
(list 4160.4576 868.9714) 
(list 4160.4499 868.9817) 
(list 4160.4414 868.9919) 
(list 4160.4321 869.0022) 
(list 4160.4225 869.0125) 
(list 4160.4128 869.0228) 
(list 4160.4033 869.0331) 
(list 4160.3943 869.0433) 
(list 4160.3861 869.0536) 
(list 4160.3789 869.0639) 
(list 4160.3731 869.0742) 
(list 4160.3686 869.0844) 
(list 4160.3658 869.0947) 
(list 4160.3647 869.105) 
(list 4160.3654 869.1153) 
(list 4160.3678 869.1256) 
(list 4160.372 869.1358) 
(list 4160.3777 869.1461) 
(list 4160.3848 869.1564) 
(list 4160.3932 869.1667) 
(list 4160.4026 869.1769) 
(list 4160.4126 869.1872) 
(list 4160.4231 869.1975) 
(list 4160.4336 869.2078) 
(list 4160.444 869.2181) 
(list 4160.4537 869.2283) 
(list 4160.4626 869.2386) 
(list 4160.4704 869.2489) 
(list 4160.4768 869.2592) 
(list 4160.4816 869.2694) 
(list 4160.4847 869.2797) 
(list 4160.4859 869.29) 
(list 4160.4859 869.29)))
(apply 'command (append '("pline") coords '("c")))
(setq tap13 (ssadd (entlast) tap13))
(command "_mirror" (entlast) "" "4160,900" "4160,901" "No")
(setq tap13 (ssadd (entlast) tap13))
(setq coords (list 
(list 4161.134 868.92) 
(list 4160.4859 868.92) 
(list 4160.4859 868.9303) 
(list 4160.4859 868.9406) 
(list 4160.4859 868.9508) 
(list 4160.4859 868.9611) 
(list 4160.4859 868.9714) 
(list 4160.4859 868.9817) 
(list 4160.4859 868.9919) 
(list 4160.4859 869.0022) 
(list 4160.4859 869.0125) 
(list 4160.4859 869.0228) 
(list 4160.4859 869.0331) 
(list 4160.4859 869.0433) 
(list 4160.4859 869.0536) 
(list 4160.4859 869.0639) 
(list 4160.4859 869.0742) 
(list 4160.4859 869.0844) 
(list 4160.4859 869.0947) 
(list 4160.4859 869.105) 
(list 4160.4859 869.1153) 
(list 4160.4859 869.1256) 
(list 4160.4859 869.1358) 
(list 4160.4859 869.1461) 
(list 4160.4859 869.1564) 
(list 4160.4859 869.1667) 
(list 4160.4859 869.1769) 
(list 4160.4859 869.1872) 
(list 4160.4859 869.1975) 
(list 4160.4859 869.2078) 
(list 4160.4859 869.2181) 
(list 4160.4859 869.2283) 
(list 4160.4859 869.2386) 
(list 4160.4859 869.2489) 
(list 4160.4859 869.2592) 
(list 4160.4859 869.2694) 
(list 4160.4859 869.2797) 
(list 4160.4859 869.29) 
(list 4161.134 869.29)))
(apply 'command (append '("pline") coords '("c")))
(setq tap13 (ssadd (entlast) tap13))
(command "_mirror" (entlast) "" "4160,900" "4160,901" "No")
(setq tap13 (ssadd (entlast) tap13))
(setq coords (list 
(list 4160 869.29) 
(list 4160.135 869.29) 
(list 4160.135 869.3003) 
(list 4160.135 869.3106) 
(list 4160.135 869.3208) 
(list 4160.135 869.3311) 
(list 4160.135 869.3414) 
(list 4160.135 869.3517) 
(list 4160.135 869.3619) 
(list 4160.135 869.3722) 
(list 4160.135 869.3825) 
(list 4160.135 869.3928) 
(list 4160.135 869.4031) 
(list 4160.135 869.4133) 
(list 4160.135 869.4236) 
(list 4160.135 869.4339) 
(list 4160.135 869.4442) 
(list 4160.135 869.4544) 
(list 4160.135 869.4647) 
(list 4160.135 869.475) 
(list 4160.135 869.4853) 
(list 4160.135 869.4956) 
(list 4160.135 869.5058) 
(list 4160.135 869.5161) 
(list 4160.135 869.5264) 
(list 4160.135 869.5367) 
(list 4160.135 869.5469) 
(list 4160.135 869.5572) 
(list 4160.135 869.5675) 
(list 4160.135 869.5778) 
(list 4160.135 869.5881) 
(list 4160.135 869.5983) 
(list 4160.135 869.6086) 
(list 4160.135 869.6189) 
(list 4160.135 869.6292) 
(list 4160.135 869.6394) 
(list 4160.135 869.6497) 
(list 4160.135 869.66) 
(list 4160 869.66)))
(apply 'command (append '("pline") coords '("c")))
(setq tap13 (ssadd (entlast) tap13))
(command "_mirror" (entlast) "" "4160,900" "4160,901" "No")
(setq tap13 (ssadd (entlast) tap13))
(setq coords (list 
(list 4160.4961 869.29) 
(list 4160.4859 869.29) 
(list 4160.4853 869.3003) 
(list 4160.4827 869.3106) 
(list 4160.4783 869.3208) 
(list 4160.4722 869.3311) 
(list 4160.4646 869.3414) 
(list 4160.4556 869.3517) 
(list 4160.4456 869.3619) 
(list 4160.4349 869.3722) 
(list 4160.4237 869.3825) 
(list 4160.4124 869.3928) 
(list 4160.4014 869.4031) 
(list 4160.391 869.4133) 
(list 4160.3816 869.4236) 
(list 4160.3733 869.4339) 
(list 4160.3665 869.4442) 
(list 4160.3614 869.4544) 
(list 4160.3582 869.4647) 
(list 4160.357 869.475) 
(list 4160.3578 869.4853) 
(list 4160.3606 869.4956) 
(list 4160.3654 869.5058) 
(list 4160.372 869.5161) 
(list 4160.3803 869.5264) 
(list 4160.39 869.5367) 
(list 4160.4007 869.5469) 
(list 4160.4123 869.5572) 
(list 4160.4243 869.5675) 
(list 4160.4364 869.5778) 
(list 4160.4482 869.5881) 
(list 4160.4594 869.5983) 
(list 4160.4696 869.6086) 
(list 4160.4785 869.6189) 
(list 4160.4857 869.6292) 
(list 4160.4912 869.6394) 
(list 4160.4947 869.6497) 
(list 4160.4961 869.66) 
(list 4160.4961 869.66)))
(apply 'command (append '("pline") coords '("c")))
(setq tap13 (ssadd (entlast) tap13))
(command "_mirror" (entlast) "" "4160,900" "4160,901" "No")
(setq tap13 (ssadd (entlast) tap13))
(setq coords (list 
(list 4161.134 869.29) 
(list 4160.4961 869.29) 
(list 4160.4961 869.3003) 
(list 4160.4961 869.3106) 
(list 4160.4961 869.3208) 
(list 4160.4961 869.3311) 
(list 4160.4961 869.3414) 
(list 4160.4961 869.3517) 
(list 4160.4961 869.3619) 
(list 4160.4961 869.3722) 
(list 4160.4961 869.3825) 
(list 4160.4961 869.3928) 
(list 4160.4961 869.4031) 
(list 4160.4961 869.4133) 
(list 4160.4961 869.4236) 
(list 4160.4961 869.4339) 
(list 4160.4961 869.4442) 
(list 4160.4961 869.4544) 
(list 4160.4961 869.4647) 
(list 4160.4961 869.475) 
(list 4160.4961 869.4853) 
(list 4160.4961 869.4956) 
(list 4160.4961 869.5058) 
(list 4160.4961 869.5161) 
(list 4160.4961 869.5264) 
(list 4160.4961 869.5367) 
(list 4160.4961 869.5469) 
(list 4160.4961 869.5572) 
(list 4160.4961 869.5675) 
(list 4160.4961 869.5778) 
(list 4160.4961 869.5881) 
(list 4160.4961 869.5983) 
(list 4160.4961 869.6086) 
(list 4160.4961 869.6189) 
(list 4160.4961 869.6292) 
(list 4160.4961 869.6394) 
(list 4160.4961 869.6497) 
(list 4160.4961 869.66) 
(list 4161.134 869.66)))
(apply 'command (append '("pline") coords '("c")))
(setq tap13 (ssadd (entlast) tap13))
(command "_mirror" (entlast) "" "4160,900" "4160,901" "No")
(setq tap13 (ssadd (entlast) tap13))
(setq coords (list 
(list 4160 869.66) 
(list 4160.135 869.66) 
(list 4160.135 869.6703) 
(list 4160.135 869.6806) 
(list 4160.135 869.6908) 
(list 4160.135 869.7011) 
(list 4160.135 869.7114) 
(list 4160.135 869.7217) 
(list 4160.135 869.7319) 
(list 4160.135 869.7422) 
(list 4160.135 869.7525) 
(list 4160.135 869.7628) 
(list 4160.135 869.7731) 
(list 4160.135 869.7833) 
(list 4160.135 869.7936) 
(list 4160.135 869.8039) 
(list 4160.135 869.8142) 
(list 4160.135 869.8244) 
(list 4160.135 869.8347) 
(list 4160.135 869.845) 
(list 4160.135 869.8553) 
(list 4160.135 869.8656) 
(list 4160.135 869.8758) 
(list 4160.135 869.8861) 
(list 4160.135 869.8964) 
(list 4160.135 869.9067) 
(list 4160.135 869.9169) 
(list 4160.135 869.9272) 
(list 4160.135 869.9375) 
(list 4160.135 869.9478) 
(list 4160.135 869.9581) 
(list 4160.135 869.9683) 
(list 4160.135 869.9786) 
(list 4160.135 869.9889) 
(list 4160.135 869.9992) 
(list 4160.135 870.0094) 
(list 4160.135 870.0197) 
(list 4160.135 870.03) 
(list 4160 870.03)))
(apply 'command (append '("pline") coords '("c")))
(setq tap13 (ssadd (entlast) tap13))
(command "_mirror" (entlast) "" "4160,900" "4160,901" "No")
(setq tap13 (ssadd (entlast) tap13))
(setq coords (list 
(list 4160.5062 869.66) 
(list 4160.4961 869.66) 
(list 4160.4953 869.6703) 
(list 4160.4923 869.6806) 
(list 4160.4872 869.6908) 
(list 4160.4802 869.7011) 
(list 4160.4715 869.7114) 
(list 4160.4613 869.7217) 
(list 4160.4499 869.7319) 
(list 4160.4376 869.7422) 
(list 4160.4249 869.7525) 
(list 4160.4121 869.7628) 
(list 4160.3996 869.7731) 
(list 4160.3878 869.7833) 
(list 4160.377 869.7936) 
(list 4160.3677 869.8039) 
(list 4160.36 869.8142) 
(list 4160.3542 869.8244) 
(list 4160.3506 869.8347) 
(list 4160.3493 869.845) 
(list 4160.3502 869.8553) 
(list 4160.3534 869.8656) 
(list 4160.3589 869.8758) 
(list 4160.3664 869.8861) 
(list 4160.3758 869.8964) 
(list 4160.3867 869.9067) 
(list 4160.3989 869.9169) 
(list 4160.4119 869.9272) 
(list 4160.4255 869.9375) 
(list 4160.4392 869.9478) 
(list 4160.4525 869.9581) 
(list 4160.4651 869.9683) 
(list 4160.4765 869.9786) 
(list 4160.4865 869.9889) 
(list 4160.4947 869.9992) 
(list 4160.5008 870.0094) 
(list 4160.5047 870.0197) 
(list 4160.5062 870.03) 
(list 4160.5062 870.03)))
(apply 'command (append '("pline") coords '("c")))
(setq tap13 (ssadd (entlast) tap13))
(command "_mirror" (entlast) "" "4160,900" "4160,901" "No")
(setq tap13 (ssadd (entlast) tap13))
(setq coords (list 
(list 4161.134 869.66) 
(list 4160.5062 869.66) 
(list 4160.5062 869.6703) 
(list 4160.5062 869.6806) 
(list 4160.5062 869.6908) 
(list 4160.5062 869.7011) 
(list 4160.5062 869.7114) 
(list 4160.5062 869.7217) 
(list 4160.5062 869.7319) 
(list 4160.5062 869.7422) 
(list 4160.5062 869.7525) 
(list 4160.5062 869.7628) 
(list 4160.5062 869.7731) 
(list 4160.5062 869.7833) 
(list 4160.5062 869.7936) 
(list 4160.5062 869.8039) 
(list 4160.5062 869.8142) 
(list 4160.5062 869.8244) 
(list 4160.5062 869.8347) 
(list 4160.5062 869.845) 
(list 4160.5062 869.8553) 
(list 4160.5062 869.8656) 
(list 4160.5062 869.8758) 
(list 4160.5062 869.8861) 
(list 4160.5062 869.8964) 
(list 4160.5062 869.9067) 
(list 4160.5062 869.9169) 
(list 4160.5062 869.9272) 
(list 4160.5062 869.9375) 
(list 4160.5062 869.9478) 
(list 4160.5062 869.9581) 
(list 4160.5062 869.9683) 
(list 4160.5062 869.9786) 
(list 4160.5062 869.9889) 
(list 4160.5062 869.9992) 
(list 4160.5062 870.0094) 
(list 4160.5062 870.0197) 
(list 4160.5062 870.03) 
(list 4161.134 870.03)))
(apply 'command (append '("pline") coords '("c")))
(setq tap13 (ssadd (entlast) tap13))
(command "_mirror" (entlast) "" "4160,900" "4160,901" "No")
(setq tap13 (ssadd (entlast) tap13))
(setq coords (list 
(list 4160 870.03) 
(list 4160.135 870.03) 
(list 4160.135 870.0403) 
(list 4160.135 870.0506) 
(list 4160.135 870.0608) 
(list 4160.135 870.0711) 
(list 4160.135 870.0814) 
(list 4160.135 870.0917) 
(list 4160.135 870.1019) 
(list 4160.135 870.1122) 
(list 4160.135 870.1225) 
(list 4160.135 870.1328) 
(list 4160.135 870.1431) 
(list 4160.135 870.1533) 
(list 4160.135 870.1636) 
(list 4160.135 870.1739) 
(list 4160.135 870.1842) 
(list 4160.135 870.1944) 
(list 4160.135 870.2047) 
(list 4160.135 870.215) 
(list 4160.135 870.2253) 
(list 4160.135 870.2356) 
(list 4160.135 870.2458) 
(list 4160.135 870.2561) 
(list 4160.135 870.2664) 
(list 4160.135 870.2767) 
(list 4160.135 870.2869) 
(list 4160.135 870.2972) 
(list 4160.135 870.3075) 
(list 4160.135 870.3178) 
(list 4160.135 870.3281) 
(list 4160.135 870.3383) 
(list 4160.135 870.3486) 
(list 4160.135 870.3589) 
(list 4160.135 870.3692) 
(list 4160.135 870.3794) 
(list 4160.135 870.3897) 
(list 4160.135 870.4) 
(list 4160 870.4)))
(apply 'command (append '("pline") coords '("c")))
(setq tap13 (ssadd (entlast) tap13))
(command "_mirror" (entlast) "" "4160,900" "4160,901" "No")
(setq tap13 (ssadd (entlast) tap13))
(setq coords (list 
(list 4160.5163 870.03) 
(list 4160.5062 870.03) 
(list 4160.5053 870.0403) 
(list 4160.5019 870.0506) 
(list 4160.4962 870.0608) 
(list 4160.4883 870.0711) 
(list 4160.4784 870.0814) 
(list 4160.4669 870.0917) 
(list 4160.4541 870.1019) 
(list 4160.4404 870.1122) 
(list 4160.4261 870.1225) 
(list 4160.4117 870.1328) 
(list 4160.3977 870.1431) 
(list 4160.3845 870.1533) 
(list 4160.3725 870.1636) 
(list 4160.362 870.1739) 
(list 4160.3534 870.1842) 
(list 4160.3471 870.1944) 
(list 4160.343 870.2047) 
(list 4160.3415 870.215) 
(list 4160.3426 870.2253) 
(list 4160.3463 870.2356) 
(list 4160.3524 870.2458) 
(list 4160.3608 870.2561) 
(list 4160.3712 870.2664) 
(list 4160.3834 870.2767) 
(list 4160.397 870.2869) 
(list 4160.4116 870.2972) 
(list 4160.4267 870.3075) 
(list 4160.4419 870.3178) 
(list 4160.4567 870.3281) 
(list 4160.4707 870.3383) 
(list 4160.4835 870.3486) 
(list 4160.4945 870.3589) 
(list 4160.5036 870.3692) 
(list 4160.5104 870.3794) 
(list 4160.5147 870.3897) 
(list 4160.5163 870.4) 
(list 4160.5163 870.4)))
(apply 'command (append '("pline") coords '("c")))
(setq tap13 (ssadd (entlast) tap13))
(command "_mirror" (entlast) "" "4160,900" "4160,901" "No")
(setq tap13 (ssadd (entlast) tap13))
(setq coords (list 
(list 4161.134 870.03) 
(list 4160.5163 870.03) 
(list 4160.5163 870.0403) 
(list 4160.5163 870.0506) 
(list 4160.5163 870.0608) 
(list 4160.5163 870.0711) 
(list 4160.5163 870.0814) 
(list 4160.5163 870.0917) 
(list 4160.5163 870.1019) 
(list 4160.5163 870.1122) 
(list 4160.5163 870.1225) 
(list 4160.5163 870.1328) 
(list 4160.5163 870.1431) 
(list 4160.5163 870.1533) 
(list 4160.5163 870.1636) 
(list 4160.5163 870.1739) 
(list 4160.5163 870.1842) 
(list 4160.5163 870.1944) 
(list 4160.5163 870.2047) 
(list 4160.5163 870.215) 
(list 4160.5163 870.2253) 
(list 4160.5163 870.2356) 
(list 4160.5163 870.2458) 
(list 4160.5163 870.2561) 
(list 4160.5163 870.2664) 
(list 4160.5163 870.2767) 
(list 4160.5163 870.2869) 
(list 4160.5163 870.2972) 
(list 4160.5163 870.3075) 
(list 4160.5163 870.3178) 
(list 4160.5163 870.3281) 
(list 4160.5163 870.3383) 
(list 4160.5163 870.3486) 
(list 4160.5163 870.3589) 
(list 4160.5163 870.3692) 
(list 4160.5163 870.3794) 
(list 4160.5163 870.3897) 
(list 4160.5163 870.4) 
(list 4161.134 870.4)))
(apply 'command (append '("pline") coords '("c")))
(setq tap13 (ssadd (entlast) tap13))
(command "_mirror" (entlast) "" "4160,900" "4160,901" "No")
(setq tap13 (ssadd (entlast) tap13))
(setq coords (list 
(list 4160 870.4) 
(list 4160.135 870.4) 
(list 4160.135 870.4103) 
(list 4160.135 870.4206) 
(list 4160.135 870.4308) 
(list 4160.135 870.4411) 
(list 4160.135 870.4514) 
(list 4160.135 870.4617) 
(list 4160.135 870.4719) 
(list 4160.135 870.4822) 
(list 4160.135 870.4925) 
(list 4160.135 870.5028) 
(list 4160.135 870.5131) 
(list 4160.135 870.5233) 
(list 4160.135 870.5336) 
(list 4160.135 870.5439) 
(list 4160.135 870.5542) 
(list 4160.135 870.5644) 
(list 4160.135 870.5747) 
(list 4160.135 870.585) 
(list 4160.135 870.5953) 
(list 4160.135 870.6056) 
(list 4160.135 870.6158) 
(list 4160.135 870.6261) 
(list 4160.135 870.6364) 
(list 4160.135 870.6467) 
(list 4160.135 870.6569) 
(list 4160.135 870.6672) 
(list 4160.135 870.6775) 
(list 4160.135 870.6878) 
(list 4160.135 870.6981) 
(list 4160.135 870.7083) 
(list 4160.135 870.7186) 
(list 4160.135 870.7289) 
(list 4160.135 870.7392) 
(list 4160.135 870.7494) 
(list 4160.135 870.7597) 
(list 4160.135 870.77) 
(list 4160 870.77)))
(apply 'command (append '("pline") coords '("c")))
(setq tap13 (ssadd (entlast) tap13))
(command "_mirror" (entlast) "" "4160,900" "4160,901" "No")
(setq tap13 (ssadd (entlast) tap13))
(setq coords (list 
(list 4160.5265 870.4) 
(list 4160.5163 870.4) 
(list 4160.5153 870.4103) 
(list 4160.5115 870.4206) 
(list 4160.5051 870.4308) 
(list 4160.4963 870.4411) 
(list 4160.4854 870.4514) 
(list 4160.4726 870.4617) 
(list 4160.4584 870.4719) 
(list 4160.4431 870.4822) 
(list 4160.4273 870.4925) 
(list 4160.4114 870.5028) 
(list 4160.3959 870.5131) 
(list 4160.3812 870.5233) 
(list 4160.3679 870.5336) 
(list 4160.3564 870.5439) 
(list 4160.3469 870.5542) 
(list 4160.3399 870.5644) 
(list 4160.3354 870.5747) 
(list 4160.3338 870.585) 
(list 4160.335 870.5953) 
(list 4160.3391 870.6056) 
(list 4160.3458 870.6158) 
(list 4160.3551 870.6261) 
(list 4160.3667 870.6364) 
(list 4160.3802 870.6467) 
(list 4160.3952 870.6569) 
(list 4160.4112 870.6672) 
(list 4160.4279 870.6775) 
(list 4160.4447 870.6878) 
(list 4160.461 870.6981) 
(list 4160.4764 870.7083) 
(list 4160.4904 870.7186) 
(list 4160.5026 870.7289) 
(list 4160.5126 870.7392) 
(list 4160.52 870.7494) 
(list 4160.5247 870.7597) 
(list 4160.5265 870.77) 
(list 4160.5265 870.77)))
(apply 'command (append '("pline") coords '("c")))
(setq tap13 (ssadd (entlast) tap13))
(command "_mirror" (entlast) "" "4160,900" "4160,901" "No")
(setq tap13 (ssadd (entlast) tap13))
(setq coords (list 
(list 4161.134 870.4) 
(list 4160.5265 870.4) 
(list 4160.5265 870.4103) 
(list 4160.5265 870.4206) 
(list 4160.5265 870.4308) 
(list 4160.5265 870.4411) 
(list 4160.5265 870.4514) 
(list 4160.5265 870.4617) 
(list 4160.5265 870.4719) 
(list 4160.5265 870.4822) 
(list 4160.5265 870.4925) 
(list 4160.5265 870.5028) 
(list 4160.5265 870.5131) 
(list 4160.5265 870.5233) 
(list 4160.5265 870.5336) 
(list 4160.5265 870.5439) 
(list 4160.5265 870.5542) 
(list 4160.5265 870.5644) 
(list 4160.5265 870.5747) 
(list 4160.5265 870.585) 
(list 4160.5265 870.5953) 
(list 4160.5265 870.6056) 
(list 4160.5265 870.6158) 
(list 4160.5265 870.6261) 
(list 4160.5265 870.6364) 
(list 4160.5265 870.6467) 
(list 4160.5265 870.6569) 
(list 4160.5265 870.6672) 
(list 4160.5265 870.6775) 
(list 4160.5265 870.6878) 
(list 4160.5265 870.6981) 
(list 4160.5265 870.7083) 
(list 4160.5265 870.7186) 
(list 4160.5265 870.7289) 
(list 4160.5265 870.7392) 
(list 4160.5265 870.7494) 
(list 4160.5265 870.7597) 
(list 4160.5265 870.77) 
(list 4161.134 870.77)))
(apply 'command (append '("pline") coords '("c")))
(setq tap13 (ssadd (entlast) tap13))
(command "_mirror" (entlast) "" "4160,900" "4160,901" "No")
(setq tap13 (ssadd (entlast) tap13))
(setq coords (list 
(list 4160 870.77) 
(list 4160.135 870.77) 
(list 4160.135 870.7803) 
(list 4160.135 870.7906) 
(list 4160.135 870.8008) 
(list 4160.135 870.8111) 
(list 4160.135 870.8214) 
(list 4160.135 870.8317) 
(list 4160.135 870.8419) 
(list 4160.135 870.8522) 
(list 4160.135 870.8625) 
(list 4160.135 870.8728) 
(list 4160.135 870.8831) 
(list 4160.135 870.8933) 
(list 4160.135 870.9036) 
(list 4160.135 870.9139) 
(list 4160.135 870.9242) 
(list 4160.135 870.9344) 
(list 4160.135 870.9447) 
(list 4160.135 870.955) 
(list 4160.135 870.9653) 
(list 4160.135 870.9756) 
(list 4160.135 870.9858) 
(list 4160.135 870.9961) 
(list 4160.135 871.0064) 
(list 4160.135 871.0167) 
(list 4160.135 871.0269) 
(list 4160.135 871.0372) 
(list 4160.135 871.0475) 
(list 4160.135 871.0578) 
(list 4160.135 871.0681) 
(list 4160.135 871.0783) 
(list 4160.135 871.0886) 
(list 4160.135 871.0989) 
(list 4160.135 871.1092) 
(list 4160.135 871.1194) 
(list 4160.135 871.1297) 
(list 4160.135 871.14) 
(list 4160 871.14)))
(apply 'command (append '("pline") coords '("c")))
(setq tap13 (ssadd (entlast) tap13))
(command "_mirror" (entlast) "" "4160,900" "4160,901" "No")
(setq tap13 (ssadd (entlast) tap13))
(setq coords (list 
(list 4160.5366 870.77) 
(list 4160.5265 870.77) 
(list 4160.5253 870.7803) 
(list 4160.5211 870.7906) 
(list 4160.514 870.8008) 
(list 4160.5044 870.8111) 
(list 4160.4923 870.8214) 
(list 4160.4783 870.8317) 
(list 4160.4626 870.8419) 
(list 4160.4459 870.8522) 
(list 4160.4285 870.8625) 
(list 4160.411 870.8728) 
(list 4160.394 870.8831) 
(list 4160.378 870.8933) 
(list 4160.3634 870.9036) 
(list 4160.3507 870.9139) 
(list 4160.3404 870.9242) 
(list 4160.3327 870.9344) 
(list 4160.3278 870.9447) 
(list 4160.3261 870.955) 
(list 4160.3274 870.9653) 
(list 4160.3319 870.9756) 
(list 4160.3393 870.9858) 
(list 4160.3495 870.9961) 
(list 4160.3621 871.0064) 
(list 4160.3769 871.0167) 
(list 4160.3933 871.0269) 
(list 4160.4109 871.0372) 
(list 4160.4291 871.0475) 
(list 4160.4474 871.0578) 
(list 4160.4652 871.0681) 
(list 4160.4821 871.0783) 
(list 4160.4973 871.0886) 
(list 4160.5106 871.0989) 
(list 4160.5215 871.1092) 
(list 4160.5296 871.1194) 
(list 4160.5347 871.1297) 
(list 4160.5366 871.14) 
(list 4160.5366 871.14)))
(apply 'command (append '("pline") coords '("c")))
(setq tap13 (ssadd (entlast) tap13))
(command "_mirror" (entlast) "" "4160,900" "4160,901" "No")
(setq tap13 (ssadd (entlast) tap13))
(setq coords (list 
(list 4161.134 870.77) 
(list 4160.5366 870.77) 
(list 4160.5366 870.7803) 
(list 4160.5366 870.7906) 
(list 4160.5366 870.8008) 
(list 4160.5366 870.8111) 
(list 4160.5366 870.8214) 
(list 4160.5366 870.8317) 
(list 4160.5366 870.8419) 
(list 4160.5366 870.8522) 
(list 4160.5366 870.8625) 
(list 4160.5366 870.8728) 
(list 4160.5366 870.8831) 
(list 4160.5366 870.8933) 
(list 4160.5366 870.9036) 
(list 4160.5366 870.9139) 
(list 4160.5366 870.9242) 
(list 4160.5366 870.9344) 
(list 4160.5366 870.9447) 
(list 4160.5366 870.955) 
(list 4160.5366 870.9653) 
(list 4160.5366 870.9756) 
(list 4160.5366 870.9858) 
(list 4160.5366 870.9961) 
(list 4160.5366 871.0064) 
(list 4160.5366 871.0167) 
(list 4160.5366 871.0269) 
(list 4160.5366 871.0372) 
(list 4160.5366 871.0475) 
(list 4160.5366 871.0578) 
(list 4160.5366 871.0681) 
(list 4160.5366 871.0783) 
(list 4160.5366 871.0886) 
(list 4160.5366 871.0989) 
(list 4160.5366 871.1092) 
(list 4160.5366 871.1194) 
(list 4160.5366 871.1297) 
(list 4160.5366 871.14) 
(list 4161.134 871.14)))
(apply 'command (append '("pline") coords '("c")))
(setq tap13 (ssadd (entlast) tap13))
(command "_mirror" (entlast) "" "4160,900" "4160,901" "No")
(setq tap13 (ssadd (entlast) tap13))
(setq coords (list 
(list 4160 871.14) 
(list 4160.135 871.14) 
(list 4160.135 871.1503) 
(list 4160.135 871.1606) 
(list 4160.135 871.1708) 
(list 4160.135 871.1811) 
(list 4160.135 871.1914) 
(list 4160.135 871.2017) 
(list 4160.135 871.2119) 
(list 4160.135 871.2222) 
(list 4160.135 871.2325) 
(list 4160.135 871.2428) 
(list 4160.135 871.2531) 
(list 4160.135 871.2633) 
(list 4160.135 871.2736) 
(list 4160.135 871.2839) 
(list 4160.135 871.2942) 
(list 4160.135 871.3044) 
(list 4160.135 871.3147) 
(list 4160.135 871.325) 
(list 4160.135 871.3353) 
(list 4160.135 871.3456) 
(list 4160.135 871.3558) 
(list 4160.135 871.3661) 
(list 4160.135 871.3764) 
(list 4160.135 871.3867) 
(list 4160.135 871.3969) 
(list 4160.135 871.4072) 
(list 4160.135 871.4175) 
(list 4160.135 871.4278) 
(list 4160.135 871.4381) 
(list 4160.135 871.4483) 
(list 4160.135 871.4586) 
(list 4160.135 871.4689) 
(list 4160.135 871.4792) 
(list 4160.135 871.4894) 
(list 4160.135 871.4997) 
(list 4160.135 871.51) 
(list 4160 871.51)))
(apply 'command (append '("pline") coords '("c")))
(setq tap13 (ssadd (entlast) tap13))
(command "_mirror" (entlast) "" "4160,900" "4160,901" "No")
(setq tap13 (ssadd (entlast) tap13))
(setq coords (list 
(list 4160.5467 871.14) 
(list 4160.5366 871.14) 
(list 4160.5352 871.1503) 
(list 4160.5307 871.1606) 
(list 4160.523 871.1708) 
(list 4160.5124 871.1811) 
(list 4160.4993 871.1914) 
(list 4160.4839 871.2017) 
(list 4160.4669 871.2119) 
(list 4160.4486 871.2222) 
(list 4160.4297 871.2325) 
(list 4160.4107 871.2428) 
(list 4160.3922 871.2531) 
(list 4160.3747 871.2633) 
(list 4160.3589 871.2736) 
(list 4160.3451 871.2839) 
(list 4160.3338 871.2942) 
(list 4160.3255 871.3044) 
(list 4160.3202 871.3147) 
(list 4160.3183 871.325) 
(list 4160.3198 871.3353) 
(list 4160.3247 871.3456) 
(list 4160.3327 871.3558) 
(list 4160.3438 871.3661) 
(list 4160.3576 871.3764) 
(list 4160.3736 871.3867) 
(list 4160.3914 871.3969) 
(list 4160.4105 871.4072) 
(list 4160.4303 871.4175) 
(list 4160.4502 871.4278) 
(list 4160.4695 871.4381) 
(list 4160.4877 871.4483) 
(list 4160.5043 871.4586) 
(list 4160.5187 871.4689) 
(list 4160.5304 871.4792) 
(list 4160.5392 871.4894) 
(list 4160.5447 871.4997) 
(list 4160.5467 871.51) 
(list 4160.5467 871.51)))
(apply 'command (append '("pline") coords '("c")))
(setq tap13 (ssadd (entlast) tap13))
(command "_mirror" (entlast) "" "4160,900" "4160,901" "No")
(setq tap13 (ssadd (entlast) tap13))
(setq coords (list 
(list 4161.134 871.14) 
(list 4160.5467 871.14) 
(list 4160.5467 871.1503) 
(list 4160.5467 871.1606) 
(list 4160.5467 871.1708) 
(list 4160.5467 871.1811) 
(list 4160.5467 871.1914) 
(list 4160.5467 871.2017) 
(list 4160.5467 871.2119) 
(list 4160.5467 871.2222) 
(list 4160.5467 871.2325) 
(list 4160.5467 871.2428) 
(list 4160.5467 871.2531) 
(list 4160.5467 871.2633) 
(list 4160.5467 871.2736) 
(list 4160.5467 871.2839) 
(list 4160.5467 871.2942) 
(list 4160.5467 871.3044) 
(list 4160.5467 871.3147) 
(list 4160.5467 871.325) 
(list 4160.5467 871.3353) 
(list 4160.5467 871.3456) 
(list 4160.5467 871.3558) 
(list 4160.5467 871.3661) 
(list 4160.5467 871.3764) 
(list 4160.5467 871.3867) 
(list 4160.5467 871.3969) 
(list 4160.5467 871.4072) 
(list 4160.5467 871.4175) 
(list 4160.5467 871.4278) 
(list 4160.5467 871.4381) 
(list 4160.5467 871.4483) 
(list 4160.5467 871.4586) 
(list 4160.5467 871.4689) 
(list 4160.5467 871.4792) 
(list 4160.5467 871.4894) 
(list 4160.5467 871.4997) 
(list 4160.5467 871.51) 
(list 4161.134 871.51)))
(apply 'command (append '("pline") coords '("c")))
(setq tap13 (ssadd (entlast) tap13))
(command "_mirror" (entlast) "" "4160,900" "4160,901" "No")
(setq tap13 (ssadd (entlast) tap13))
(setq coords (list 
(list 4160 871.51) 
(list 4160.135 871.51) 
(list 4160.135 871.5203) 
(list 4160.135 871.5306) 
(list 4160.135 871.5408) 
(list 4160.135 871.5511) 
(list 4160.135 871.5614) 
(list 4160.135 871.5717) 
(list 4160.135 871.5819) 
(list 4160.135 871.5922) 
(list 4160.135 871.6025) 
(list 4160.135 871.6128) 
(list 4160.135 871.6231) 
(list 4160.135 871.6333) 
(list 4160.135 871.6436) 
(list 4160.135 871.6539) 
(list 4160.135 871.6642) 
(list 4160.135 871.6744) 
(list 4160.135 871.6847) 
(list 4160.135 871.695) 
(list 4160.135 871.7053) 
(list 4160.135 871.7156) 
(list 4160.135 871.7258) 
(list 4160.135 871.7361) 
(list 4160.135 871.7464) 
(list 4160.135 871.7567) 
(list 4160.135 871.7669) 
(list 4160.135 871.7772) 
(list 4160.135 871.7875) 
(list 4160.135 871.7978) 
(list 4160.135 871.8081) 
(list 4160.135 871.8183) 
(list 4160.135 871.8286) 
(list 4160.135 871.8389) 
(list 4160.135 871.8492) 
(list 4160.135 871.8594) 
(list 4160.135 871.8697) 
(list 4160.135 871.88) 
(list 4160 871.88)))
(apply 'command (append '("pline") coords '("c")))
(setq tap13 (ssadd (entlast) tap13))
(command "_mirror" (entlast) "" "4160,900" "4160,901" "No")
(setq tap13 (ssadd (entlast) tap13))
(setq coords (list 
(list 4160.5569 871.51) 
(list 4160.5467 871.51) 
(list 4160.5452 871.5203) 
(list 4160.5403 871.5306) 
(list 4160.5319 871.5408) 
(list 4160.5205 871.5511) 
(list 4160.5062 871.5614) 
(list 4160.4896 871.5717) 
(list 4160.4711 871.5819) 
(list 4160.4514 871.5922) 
(list 4160.4309 871.6025) 
(list 4160.4103 871.6128) 
(list 4160.3903 871.6231) 
(list 4160.3714 871.6333) 
(list 4160.3543 871.6436) 
(list 4160.3394 871.6539) 
(list 4160.3273 871.6642) 
(list 4160.3183 871.6744) 
(list 4160.3126 871.6847) 
(list 4160.3106 871.695) 
(list 4160.3122 871.7053) 
(list 4160.3175 871.7156) 
(list 4160.3262 871.7258) 
(list 4160.3382 871.7361) 
(list 4160.353 871.7464) 
(list 4160.3704 871.7567) 
(list 4160.3896 871.7669) 
(list 4160.4102 871.7772) 
(list 4160.4315 871.7875) 
(list 4160.4529 871.7978) 
(list 4160.4737 871.8081) 
(list 4160.4934 871.8183) 
(list 4160.5112 871.8286) 
(list 4160.5267 871.8389) 
(list 4160.5394 871.8492) 
(list 4160.5488 871.8594) 
(list 4160.5547 871.8697) 
(list 4160.5569 871.88) 
(list 4160.5569 871.88)))
(apply 'command (append '("pline") coords '("c")))
(setq tap13 (ssadd (entlast) tap13))
(command "_mirror" (entlast) "" "4160,900" "4160,901" "No")
(setq tap13 (ssadd (entlast) tap13))
(setq coords (list 
(list 4161.134 871.51) 
(list 4160.5569 871.51) 
(list 4160.5569 871.5203) 
(list 4160.5569 871.5306) 
(list 4160.5569 871.5408) 
(list 4160.5569 871.5511) 
(list 4160.5569 871.5614) 
(list 4160.5569 871.5717) 
(list 4160.5569 871.5819) 
(list 4160.5569 871.5922) 
(list 4160.5569 871.6025) 
(list 4160.5569 871.6128) 
(list 4160.5569 871.6231) 
(list 4160.5569 871.6333) 
(list 4160.5569 871.6436) 
(list 4160.5569 871.6539) 
(list 4160.5569 871.6642) 
(list 4160.5569 871.6744) 
(list 4160.5569 871.6847) 
(list 4160.5569 871.695) 
(list 4160.5569 871.7053) 
(list 4160.5569 871.7156) 
(list 4160.5569 871.7258) 
(list 4160.5569 871.7361) 
(list 4160.5569 871.7464) 
(list 4160.5569 871.7567) 
(list 4160.5569 871.7669) 
(list 4160.5569 871.7772) 
(list 4160.5569 871.7875) 
(list 4160.5569 871.7978) 
(list 4160.5569 871.8081) 
(list 4160.5569 871.8183) 
(list 4160.5569 871.8286) 
(list 4160.5569 871.8389) 
(list 4160.5569 871.8492) 
(list 4160.5569 871.8594) 
(list 4160.5569 871.8697) 
(list 4160.5569 871.88) 
(list 4161.134 871.88)))
(apply 'command (append '("pline") coords '("c")))
(setq tap13 (ssadd (entlast) tap13))
(command "_mirror" (entlast) "" "4160,900" "4160,901" "No")
(setq tap13 (ssadd (entlast) tap13))
(setq coords (list 
(list 4160 871.88) 
(list 4160.135 871.88) 
(list 4160.135 871.8903) 
(list 4160.135 871.9006) 
(list 4160.135 871.9108) 
(list 4160.135 871.9211) 
(list 4160.135 871.9314) 
(list 4160.135 871.9417) 
(list 4160.135 871.9519) 
(list 4160.135 871.9622) 
(list 4160.135 871.9725) 
(list 4160.135 871.9828) 
(list 4160.135 871.9931) 
(list 4160.135 872.0033) 
(list 4160.135 872.0136) 
(list 4160.135 872.0239) 
(list 4160.135 872.0342) 
(list 4160.135 872.0444) 
(list 4160.135 872.0547) 
(list 4160.135 872.065) 
(list 4160.135 872.0753) 
(list 4160.135 872.0856) 
(list 4160.135 872.0958) 
(list 4160.135 872.1061) 
(list 4160.135 872.1164) 
(list 4160.135 872.1267) 
(list 4160.135 872.1369) 
(list 4160.135 872.1472) 
(list 4160.135 872.1575) 
(list 4160.135 872.1678) 
(list 4160.135 872.1781) 
(list 4160.135 872.1883) 
(list 4160.135 872.1986) 
(list 4160.135 872.2089) 
(list 4160.135 872.2192) 
(list 4160.135 872.2294) 
(list 4160.135 872.2397) 
(list 4160.135 872.25) 
(list 4160 872.25)))
(apply 'command (append '("pline") coords '("c")))
(setq tap13 (ssadd (entlast) tap13))
(command "_mirror" (entlast) "" "4160,900" "4160,901" "No")
(setq tap13 (ssadd (entlast) tap13))
(setq coords (list 
(list 4160.567 871.88) 
(list 4160.5569 871.88) 
(list 4160.5552 871.8903) 
(list 4160.5499 871.9006) 
(list 4160.5409 871.9108) 
(list 4160.5285 871.9211) 
(list 4160.5132 871.9314) 
(list 4160.4953 871.9417) 
(list 4160.4754 871.9519) 
(list 4160.4541 871.9622) 
(list 4160.4321 871.9725) 
(list 4160.41 871.9828) 
(list 4160.3885 871.9931) 
(list 4160.3682 872.0033) 
(list 4160.3498 872.0136) 
(list 4160.3338 872.0239) 
(list 4160.3208 872.0342) 
(list 4160.3111 872.0444) 
(list 4160.305 872.0547) 
(list 4160.3029 872.065) 
(list 4160.3046 872.0753) 
(list 4160.3103 872.0856) 
(list 4160.3197 872.0958) 
(list 4160.3325 872.1061) 
(list 4160.3485 872.1164) 
(list 4160.3671 872.1267) 
(list 4160.3877 872.1369) 
(list 4160.4098 872.1472) 
(list 4160.4327 872.1575) 
(list 4160.4557 872.1678) 
(list 4160.478 872.1781) 
(list 4160.4991 872.1883) 
(list 4160.5182 872.1986) 
(list 4160.5348 872.2089) 
(list 4160.5483 872.2192) 
(list 4160.5584 872.2294) 
(list 4160.5647 872.2397) 
(list 4160.567 872.25) 
(list 4160.567 872.25)))
(apply 'command (append '("pline") coords '("c")))
(setq tap13 (ssadd (entlast) tap13))
(command "_mirror" (entlast) "" "4160,900" "4160,901" "No")
(setq tap13 (ssadd (entlast) tap13))
(setq coords (list 
(list 4161.134 871.88) 
(list 4160.567 871.88) 
(list 4160.567 871.8903) 
(list 4160.567 871.9006) 
(list 4160.567 871.9108) 
(list 4160.567 871.9211) 
(list 4160.567 871.9314) 
(list 4160.567 871.9417) 
(list 4160.567 871.9519) 
(list 4160.567 871.9622) 
(list 4160.567 871.9725) 
(list 4160.567 871.9828) 
(list 4160.567 871.9931) 
(list 4160.567 872.0033) 
(list 4160.567 872.0136) 
(list 4160.567 872.0239) 
(list 4160.567 872.0342) 
(list 4160.567 872.0444) 
(list 4160.567 872.0547) 
(list 4160.567 872.065) 
(list 4160.567 872.0753) 
(list 4160.567 872.0856) 
(list 4160.567 872.0958) 
(list 4160.567 872.1061) 
(list 4160.567 872.1164) 
(list 4160.567 872.1267) 
(list 4160.567 872.1369) 
(list 4160.567 872.1472) 
(list 4160.567 872.1575) 
(list 4160.567 872.1678) 
(list 4160.567 872.1781) 
(list 4160.567 872.1883) 
(list 4160.567 872.1986) 
(list 4160.567 872.2089) 
(list 4160.567 872.2192) 
(list 4160.567 872.2294) 
(list 4160.567 872.2397) 
(list 4160.567 872.25) 
(list 4161.134 872.25)))
(apply 'command (append '("pline") coords '("c")))
(setq tap13 (ssadd (entlast) tap13))
(command "_mirror" (entlast) "" "4160,900" "4160,901" "No")
(setq tap13 (ssadd (entlast) tap13))
(command "_block" "blktap13" "4160,900" tap13 "")
(command "_insert" "blktap13" "4160,900" "1" "1" "0")
(command "_insert" "blktap13" "4160,900" "1" "1" "180")
(setq uc13 nil)
(setq uc13 (ssadd))
(setq coords (list 
(list 0 -0.185) 
(list 0.135 -0.185) 
(list 0.135 -0.17472) 
(list 0.135 -0.16444) 
(list 0.135 -0.15417) 
(list 0.135 -0.14389) 
(list 0.135 -0.13361) 
(list 0.135 -0.12333) 
(list 0.135 -0.11306) 
(list 0.135 -0.10278) 
(list 0.135 -0.0925) 
(list 0.135 -0.082222) 
(list 0.135 -0.071944) 
(list 0.135 -0.061667) 
(list 0.135 -0.051389) 
(list 0.135 -0.041111) 
(list 0.135 -0.030833) 
(list 0.135 -0.020556) 
(list 0.135 -0.010278) 
(list 0.135 0) 
(list 0.135 0.010278) 
(list 0.135 0.020556) 
(list 0.135 0.030833) 
(list 0.135 0.041111) 
(list 0.135 0.051389) 
(list 0.135 0.061667) 
(list 0.135 0.071944) 
(list 0.135 0.082222) 
(list 0.135 0.0925) 
(list 0.135 0.10278) 
(list 0.135 0.11306) 
(list 0.135 0.12333) 
(list 0.135 0.13361) 
(list 0.135 0.14389) 
(list 0.135 0.15417) 
(list 0.135 0.16444) 
(list 0.135 0.17472) 
(list 0.135 0.185) 
(list 0 0.185)))
(apply 'command (append '("pline") coords '("c")))
(setq uc13 (ssadd (entlast) uc13))
(setq coords (list 
(list 1.134 -0.185) 
(list 0.567 -0.185) 
(list 0.56496 -0.17472) 
(list 0.55892 -0.16444) 
(list 0.54905 -0.15417) 
(list 0.53565 -0.14389) 
(list 0.51913 -0.13361) 
(list 0.5 -0.12333) 
(list 0.47883 -0.11306) 
(list 0.45627 -0.10278) 
(list 0.433 -0.0925) 
(list 0.40973 -0.082222) 
(list 0.38717 -0.071944) 
(list 0.366 -0.061667) 
(list 0.34687 -0.051389) 
(list 0.33035 -0.041111) 
(list 0.31695 -0.030833) 
(list 0.30708 -0.020556) 
(list 0.30104 -0.010278) 
(list 0.299 0) 
(list 0.30104 0.010278) 
(list 0.30708 0.020556) 
(list 0.31695 0.030833) 
(list 0.33035 0.041111) 
(list 0.34687 0.051389) 
(list 0.366 0.061667) 
(list 0.38717 0.071944) 
(list 0.40973 0.082222) 
(list 0.433 0.0925) 
(list 0.45627 0.10278) 
(list 0.47883 0.11306) 
(list 0.5 0.12333) 
(list 0.51913 0.13361) 
(list 0.53565 0.14389) 
(list 0.54905 0.15417) 
(list 0.55892 0.16444) 
(list 0.56496 0.17472) 
(list 0.567 0.185) 
(list 1.134 0.185)))
(apply 'command (append '("pline") coords '("c")))
(setq uc13 (ssadd (entlast) uc13))
(command "_block" "blkuc13" "0,0.185" uc13 "")
(command "_insert" "blkuc13" "4160,872.62" "1" "1" "0")
(command "_insert" "blkuc13" "4160,872.25" "1" "1" "180")
(command "_insert" "blkuc13" "4160,872.99" "1" "1" "0")
(command "_insert" "blkuc13" "4160,872.62" "1" "1" "180")
(command "_insert" "blkuc13" "4160,873.36" "1" "1" "0")
(command "_insert" "blkuc13" "4160,872.99" "1" "1" "180")
(command "_insert" "blkuc13" "4160,873.73" "1" "1" "0")
(command "_insert" "blkuc13" "4160,873.36" "1" "1" "180")
(command "_insert" "blkuc13" "4160,874.1" "1" "1" "0")
(command "_insert" "blkuc13" "4160,873.73" "1" "1" "180")
(command "_insert" "blkuc13" "4160,874.47" "1" "1" "0")
(command "_insert" "blkuc13" "4160,874.1" "1" "1" "180")
(command "_insert" "blkuc13" "4160,874.84" "1" "1" "0")
(command "_insert" "blkuc13" "4160,874.47" "1" "1" "180")
(command "_insert" "blkuc13" "4160,875.21" "1" "1" "0")
(command "_insert" "blkuc13" "4160,874.84" "1" "1" "180")
(command "_insert" "blkuc13" "4160,875.58" "1" "1" "0")
(command "_insert" "blkuc13" "4160,875.21" "1" "1" "180")
(command "_insert" "blkuc13" "4160,875.95" "1" "1" "0")
(command "_insert" "blkuc13" "4160,875.58" "1" "1" "180")
(command "_insert" "blkuc13" "4160,876.32" "1" "1" "0")
(command "_insert" "blkuc13" "4160,875.95" "1" "1" "180")
(command "_insert" "blkuc13" "4160,876.69" "1" "1" "0")
(command "_insert" "blkuc13" "4160,876.32" "1" "1" "180")
(command "_insert" "blkuc13" "4160,877.06" "1" "1" "0")
(command "_insert" "blkuc13" "4160,876.69" "1" "1" "180")
(command "_insert" "blkuc13" "4160,877.43" "1" "1" "0")
(command "_insert" "blkuc13" "4160,877.06" "1" "1" "180")
(command "_insert" "blkuc13" "4160,877.8" "1" "1" "0")
(command "_insert" "blkuc13" "4160,877.43" "1" "1" "180")
(command "_insert" "blkuc13" "4160,878.17" "1" "1" "0")
(command "_insert" "blkuc13" "4160,877.8" "1" "1" "180")
(command "_insert" "blkuc13" "4160,878.54" "1" "1" "0")
(command "_insert" "blkuc13" "4160,878.17" "1" "1" "180")
(command "_insert" "blkuc13" "4160,878.91" "1" "1" "0")
(command "_insert" "blkuc13" "4160,878.54" "1" "1" "180")
(command "_insert" "blkuc13" "4160,879.28" "1" "1" "0")
(command "_insert" "blkuc13" "4160,878.91" "1" "1" "180")
(command "_insert" "blkuc13" "4160,879.65" "1" "1" "0")
(command "_insert" "blkuc13" "4160,879.28" "1" "1" "180")
(command "_insert" "blkuc13" "4160,880.02" "1" "1" "0")
(command "_insert" "blkuc13" "4160,879.65" "1" "1" "180")
(command "_insert" "blkuc13" "4160,880.39" "1" "1" "0")
(command "_insert" "blkuc13" "4160,880.02" "1" "1" "180")
(command "_insert" "blkuc13" "4160,880.76" "1" "1" "0")
(command "_insert" "blkuc13" "4160,880.39" "1" "1" "180")
(command "_insert" "blkuc13" "4160,881.13" "1" "1" "0")
(command "_insert" "blkuc13" "4160,880.76" "1" "1" "180")
(command "_insert" "blkuc13" "4160,881.5" "1" "1" "0")
(command "_insert" "blkuc13" "4160,881.13" "1" "1" "180")
(command "_insert" "blkuc13" "4160,881.87" "1" "1" "0")
(command "_insert" "blkuc13" "4160,881.5" "1" "1" "180")
(command "_insert" "blkuc13" "4160,882.24" "1" "1" "0")
(command "_insert" "blkuc13" "4160,881.87" "1" "1" "180")
(command "_insert" "blkuc13" "4160,882.61" "1" "1" "0")
(command "_insert" "blkuc13" "4160,882.24" "1" "1" "180")
(command "_insert" "blkuc13" "4160,882.98" "1" "1" "0")
(command "_insert" "blkuc13" "4160,882.61" "1" "1" "180")
(command "_insert" "blkuc13" "4160,883.35" "1" "1" "0")
(command "_insert" "blkuc13" "4160,882.98" "1" "1" "180")
(command "_insert" "blkuc13" "4160,883.72" "1" "1" "0")
(command "_insert" "blkuc13" "4160,883.35" "1" "1" "180")
(command "_insert" "blkuc13" "4160,884.09" "1" "1" "0")
(command "_insert" "blkuc13" "4160,883.72" "1" "1" "180")
(command "_insert" "blkuc13" "4160,884.46" "1" "1" "0")
(command "_insert" "blkuc13" "4160,884.09" "1" "1" "180")
(command "_insert" "blkuc13" "4160,884.83" "1" "1" "0")
(command "_insert" "blkuc13" "4160,884.46" "1" "1" "180")
(command "_insert" "blkuc13" "4160,885.2" "1" "1" "0")
(command "_insert" "blkuc13" "4160,884.83" "1" "1" "180")
(command "_insert" "blkuc13" "4160,885.57" "1" "1" "0")
(command "_insert" "blkuc13" "4160,885.2" "1" "1" "180")
(command "_insert" "blkuc13" "4160,885.94" "1" "1" "0")
(command "_insert" "blkuc13" "4160,885.57" "1" "1" "180")
(command "_insert" "blkuc13" "4160,886.31" "1" "1" "0")
(command "_insert" "blkuc13" "4160,885.94" "1" "1" "180")
(command "_insert" "blkuc13" "4160,886.68" "1" "1" "0")
(command "_insert" "blkuc13" "4160,886.31" "1" "1" "180")
(command "_insert" "blkuc13" "4160,887.05" "1" "1" "0")
(command "_insert" "blkuc13" "4160,886.68" "1" "1" "180")
(command "_insert" "blkuc13" "4160,887.42" "1" "1" "0")
(command "_insert" "blkuc13" "4160,887.05" "1" "1" "180")
(command "_insert" "blkuc13" "4160,887.79" "1" "1" "0")
(command "_insert" "blkuc13" "4160,887.42" "1" "1" "180")
(command "_insert" "blkuc13" "4160,888.16" "1" "1" "0")
(command "_insert" "blkuc13" "4160,887.79" "1" "1" "180")
(command "_insert" "blkuc13" "4160,888.53" "1" "1" "0")
(command "_insert" "blkuc13" "4160,888.16" "1" "1" "180")
(command "_insert" "blkuc13" "4160,888.9" "1" "1" "0")
(command "_insert" "blkuc13" "4160,888.53" "1" "1" "180")
(command "_insert" "blkuc13" "4160,889.27" "1" "1" "0")
(command "_insert" "blkuc13" "4160,888.9" "1" "1" "180")
(command "_insert" "blkuc13" "4160,889.64" "1" "1" "0")
(command "_insert" "blkuc13" "4160,889.27" "1" "1" "180")
(command "_insert" "blkuc13" "4160,890.01" "1" "1" "0")
(command "_insert" "blkuc13" "4160,889.64" "1" "1" "180")
(command "_insert" "blkuc13" "4160,890.38" "1" "1" "0")
(command "_insert" "blkuc13" "4160,890.01" "1" "1" "180")
(command "_insert" "blkuc13" "4160,890.75" "1" "1" "0")
(command "_insert" "blkuc13" "4160,890.38" "1" "1" "180")
(command "_insert" "blkuc13" "4160,891.12" "1" "1" "0")
(command "_insert" "blkuc13" "4160,890.75" "1" "1" "180")
(command "_insert" "blkuc13" "4160,891.49" "1" "1" "0")
(command "_insert" "blkuc13" "4160,891.12" "1" "1" "180")
(command "_insert" "blkuc13" "4160,891.86" "1" "1" "0")
(command "_insert" "blkuc13" "4160,891.49" "1" "1" "180")
(command "_insert" "blkuc13" "4160,892.23" "1" "1" "0")
(command "_insert" "blkuc13" "4160,891.86" "1" "1" "180")
(command "_insert" "blkuc13" "4160,892.6" "1" "1" "0")
(command "_insert" "blkuc13" "4160,892.23" "1" "1" "180")
(command "_insert" "blkuc13" "4160,892.97" "1" "1" "0")
(command "_insert" "blkuc13" "4160,892.6" "1" "1" "180")
(command "_insert" "blkuc13" "4160,893.34" "1" "1" "0")
(command "_insert" "blkuc13" "4160,892.97" "1" "1" "180")
(command "_insert" "blkuc13" "4160,893.71" "1" "1" "0")
(command "_insert" "blkuc13" "4160,893.34" "1" "1" "180")
(command "_insert" "blkuc13" "4160,894.08" "1" "1" "0")
(command "_insert" "blkuc13" "4160,893.71" "1" "1" "180")
(command "_insert" "blkuc13" "4160,894.45" "1" "1" "0")
(command "_insert" "blkuc13" "4160,894.08" "1" "1" "180")
(command "_insert" "blkuc13" "4160,894.82" "1" "1" "0")
(command "_insert" "blkuc13" "4160,894.45" "1" "1" "180")
(command "_insert" "blkuc13" "4160,895.19" "1" "1" "0")
(command "_insert" "blkuc13" "4160,894.82" "1" "1" "180")
(command "_insert" "blkuc13" "4160,895.56" "1" "1" "0")
(command "_insert" "blkuc13" "4160,895.19" "1" "1" "180")
(command "_insert" "blkuc13" "4160,895.93" "1" "1" "0")
(command "_insert" "blkuc13" "4160,895.56" "1" "1" "180")
(command "_insert" "blkuc13" "4160,896.3" "1" "1" "0")
(command "_insert" "blkuc13" "4160,895.93" "1" "1" "180")
(command "_insert" "blkuc13" "4160,896.67" "1" "1" "0")
(command "_insert" "blkuc13" "4160,896.3" "1" "1" "180")
(command "_insert" "blkuc13" "4160,897.04" "1" "1" "0")
(command "_insert" "blkuc13" "4160,896.67" "1" "1" "180")
(command "_insert" "blkuc13" "4160,897.41" "1" "1" "0")
(command "_insert" "blkuc13" "4160,897.04" "1" "1" "180")
(command "_insert" "blkuc13" "4160,897.78" "1" "1" "0")
(command "_insert" "blkuc13" "4160,897.41" "1" "1" "180")
(command "_insert" "blkuc13" "4160,898.15" "1" "1" "0")
(command "_insert" "blkuc13" "4160,897.78" "1" "1" "180")
(command "_insert" "blkuc13" "4160,898.52" "1" "1" "0")
(command "_insert" "blkuc13" "4160,898.15" "1" "1" "180")
(command "_insert" "blkuc13" "4160,898.89" "1" "1" "0")
(command "_insert" "blkuc13" "4160,898.52" "1" "1" "180")
(command "_insert" "blkuc13" "4160,899.26" "1" "1" "0")
(command "_insert" "blkuc13" "4160,898.89" "1" "1" "180")
(command "_insert" "blkuc13" "4160,899.63" "1" "1" "0")
(command "_insert" "blkuc13" "4160,899.26" "1" "1" "180")
(command "_insert" "blkuc13" "4160,900" "1" "1" "0")
(command "_insert" "blkuc13" "4160,899.63" "1" "1" "180")
(command "_insert" "blkuc13" "4160,900.37" "1" "1" "0")
(command "_insert" "blkuc13" "4160,900" "1" "1" "180")
(command "_insert" "blkuc13" "4160,900.74" "1" "1" "0")
(command "_insert" "blkuc13" "4160,900.37" "1" "1" "180")
(command "_insert" "blkuc13" "4160,901.11" "1" "1" "0")
(command "_insert" "blkuc13" "4160,900.74" "1" "1" "180")
(command "_insert" "blkuc13" "4160,901.48" "1" "1" "0")
(command "_insert" "blkuc13" "4160,901.11" "1" "1" "180")
(command "_insert" "blkuc13" "4160,901.85" "1" "1" "0")
(command "_insert" "blkuc13" "4160,901.48" "1" "1" "180")
(command "_insert" "blkuc13" "4160,902.22" "1" "1" "0")
(command "_insert" "blkuc13" "4160,901.85" "1" "1" "180")
(command "_insert" "blkuc13" "4160,902.59" "1" "1" "0")
(command "_insert" "blkuc13" "4160,902.22" "1" "1" "180")
(command "_insert" "blkuc13" "4160,902.96" "1" "1" "0")
(command "_insert" "blkuc13" "4160,902.59" "1" "1" "180")
(command "_insert" "blkuc13" "4160,903.33" "1" "1" "0")
(command "_insert" "blkuc13" "4160,902.96" "1" "1" "180")
(command "_insert" "blkuc13" "4160,903.7" "1" "1" "0")
(command "_insert" "blkuc13" "4160,903.33" "1" "1" "180")
(command "_insert" "blkuc13" "4160,904.07" "1" "1" "0")
(command "_insert" "blkuc13" "4160,903.7" "1" "1" "180")
(command "_insert" "blkuc13" "4160,904.44" "1" "1" "0")
(command "_insert" "blkuc13" "4160,904.07" "1" "1" "180")
(command "_insert" "blkuc13" "4160,904.81" "1" "1" "0")
(command "_insert" "blkuc13" "4160,904.44" "1" "1" "180")
(command "_insert" "blkuc13" "4160,905.18" "1" "1" "0")
(command "_insert" "blkuc13" "4160,904.81" "1" "1" "180")
(command "_insert" "blkuc13" "4160,905.55" "1" "1" "0")
(command "_insert" "blkuc13" "4160,905.18" "1" "1" "180")
(command "_insert" "blkuc13" "4160,905.92" "1" "1" "0")
(command "_insert" "blkuc13" "4160,905.55" "1" "1" "180")
(command "_insert" "blkuc13" "4160,906.29" "1" "1" "0")
(command "_insert" "blkuc13" "4160,905.92" "1" "1" "180")
(command "_insert" "blkuc13" "4160,906.66" "1" "1" "0")
(command "_insert" "blkuc13" "4160,906.29" "1" "1" "180")
(command "_insert" "blkuc13" "4160,907.03" "1" "1" "0")
(command "_insert" "blkuc13" "4160,906.66" "1" "1" "180")
(command "_insert" "blkuc13" "4160,907.4" "1" "1" "0")
(command "_insert" "blkuc13" "4160,907.03" "1" "1" "180")
(command "_insert" "blkuc13" "4160,907.77" "1" "1" "0")
(command "_insert" "blkuc13" "4160,907.4" "1" "1" "180")
(command "_insert" "blkuc13" "4160,908.14" "1" "1" "0")
(command "_insert" "blkuc13" "4160,907.77" "1" "1" "180")
(command "_insert" "blkuc13" "4160,908.51" "1" "1" "0")
(command "_insert" "blkuc13" "4160,908.14" "1" "1" "180")
(command "_insert" "blkuc13" "4160,908.88" "1" "1" "0")
(command "_insert" "blkuc13" "4160,908.51" "1" "1" "180")
(command "_insert" "blkuc13" "4160,909.25" "1" "1" "0")
(command "_insert" "blkuc13" "4160,908.88" "1" "1" "180")
(command "_insert" "blkuc13" "4160,909.62" "1" "1" "0")
(command "_insert" "blkuc13" "4160,909.25" "1" "1" "180")
(command "_insert" "blkuc13" "4160,909.99" "1" "1" "0")
(command "_insert" "blkuc13" "4160,909.62" "1" "1" "180")
(command "_insert" "blkuc13" "4160,910.36" "1" "1" "0")
(command "_insert" "blkuc13" "4160,909.99" "1" "1" "180")
(command "_insert" "blkuc13" "4160,910.73" "1" "1" "0")
(command "_insert" "blkuc13" "4160,910.36" "1" "1" "180")
(command "_insert" "blkuc13" "4160,911.1" "1" "1" "0")
(command "_insert" "blkuc13" "4160,910.73" "1" "1" "180")
(command "_insert" "blkuc13" "4160,911.47" "1" "1" "0")
(command "_insert" "blkuc13" "4160,911.1" "1" "1" "180")
(command "_insert" "blkuc13" "4160,911.84" "1" "1" "0")
(command "_insert" "blkuc13" "4160,911.47" "1" "1" "180")
(command "_insert" "blkuc13" "4160,912.21" "1" "1" "0")
(command "_insert" "blkuc13" "4160,911.84" "1" "1" "180")
(command "_insert" "blkuc13" "4160,912.58" "1" "1" "0")
(command "_insert" "blkuc13" "4160,912.21" "1" "1" "180")
(command "_insert" "blkuc13" "4160,912.95" "1" "1" "0")
(command "_insert" "blkuc13" "4160,912.58" "1" "1" "180")
(command "_insert" "blkuc13" "4160,913.32" "1" "1" "0")
(command "_insert" "blkuc13" "4160,912.95" "1" "1" "180")
(command "_insert" "blkuc13" "4160,913.69" "1" "1" "0")
(command "_insert" "blkuc13" "4160,913.32" "1" "1" "180")
(command "_insert" "blkuc13" "4160,914.06" "1" "1" "0")
(command "_insert" "blkuc13" "4160,913.69" "1" "1" "180")
(command "_insert" "blkuc13" "4160,914.43" "1" "1" "0")
(command "_insert" "blkuc13" "4160,914.06" "1" "1" "180")
(command "_insert" "blkuc13" "4160,914.8" "1" "1" "0")
(command "_insert" "blkuc13" "4160,914.43" "1" "1" "180")
(command "_insert" "blkuc13" "4160,915.17" "1" "1" "0")
(command "_insert" "blkuc13" "4160,914.8" "1" "1" "180")
(command "_insert" "blkuc13" "4160,915.54" "1" "1" "0")
(command "_insert" "blkuc13" "4160,915.17" "1" "1" "180")
(command "_insert" "blkuc13" "4160,915.91" "1" "1" "0")
(command "_insert" "blkuc13" "4160,915.54" "1" "1" "180")
(command "_insert" "blkuc13" "4160,916.28" "1" "1" "0")
(command "_insert" "blkuc13" "4160,915.91" "1" "1" "180")
(command "_insert" "blkuc13" "4160,916.65" "1" "1" "0")
(command "_insert" "blkuc13" "4160,916.28" "1" "1" "180")
(command "_insert" "blkuc13" "4160,917.02" "1" "1" "0")
(command "_insert" "blkuc13" "4160,916.65" "1" "1" "180")
(command "_insert" "blkuc13" "4160,917.39" "1" "1" "0")
(command "_insert" "blkuc13" "4160,917.02" "1" "1" "180")
(command "_insert" "blkuc13" "4160,917.76" "1" "1" "0")
(command "_insert" "blkuc13" "4160,917.39" "1" "1" "180")
(command "_insert" "blkuc13" "4160,918.13" "1" "1" "0")
(command "_insert" "blkuc13" "4160,917.76" "1" "1" "180")
(command "_insert" "blkuc13" "4160,918.5" "1" "1" "0")
(command "_insert" "blkuc13" "4160,918.13" "1" "1" "180")
(command "_insert" "blkuc13" "4160,918.87" "1" "1" "0")
(command "_insert" "blkuc13" "4160,918.5" "1" "1" "180")
(command "_insert" "blkuc13" "4160,919.24" "1" "1" "0")
(command "_insert" "blkuc13" "4160,918.87" "1" "1" "180")
(command "_insert" "blkuc13" "4160,919.61" "1" "1" "0")
(command "_insert" "blkuc13" "4160,919.24" "1" "1" "180")
(command "_insert" "blkuc13" "4160,919.98" "1" "1" "0")
(command "_insert" "blkuc13" "4160,919.61" "1" "1" "180")
(command "_insert" "blkuc13" "4160,920.35" "1" "1" "0")
(command "_insert" "blkuc13" "4160,919.98" "1" "1" "180")
(command "_insert" "blkuc13" "4160,920.72" "1" "1" "0")
(command "_insert" "blkuc13" "4160,920.35" "1" "1" "180")
(command "_insert" "blkuc13" "4160,921.09" "1" "1" "0")
(command "_insert" "blkuc13" "4160,920.72" "1" "1" "180")
(command "_insert" "blkuc13" "4160,921.46" "1" "1" "0")
(command "_insert" "blkuc13" "4160,921.09" "1" "1" "180")
(command "_insert" "blkuc13" "4160,921.83" "1" "1" "0")
(command "_insert" "blkuc13" "4160,921.46" "1" "1" "180")
(command "_insert" "blkuc13" "4160,922.2" "1" "1" "0")
(command "_insert" "blkuc13" "4160,921.83" "1" "1" "180")
(command "_insert" "blkuc13" "4160,922.57" "1" "1" "0")
(command "_insert" "blkuc13" "4160,922.2" "1" "1" "180")
(command "_insert" "blkuc13" "4160,922.94" "1" "1" "0")
(command "_insert" "blkuc13" "4160,922.57" "1" "1" "180")
(command "_insert" "blkuc13" "4160,923.31" "1" "1" "0")
(command "_insert" "blkuc13" "4160,922.94" "1" "1" "180")
(command "_insert" "blkuc13" "4160,923.68" "1" "1" "0")
(command "_insert" "blkuc13" "4160,923.31" "1" "1" "180")
(command "_insert" "blkuc13" "4160,924.05" "1" "1" "0")
(command "_insert" "blkuc13" "4160,923.68" "1" "1" "180")
(command "_insert" "blkuc13" "4160,924.42" "1" "1" "0")
(command "_insert" "blkuc13" "4160,924.05" "1" "1" "180")
(command "_insert" "blkuc13" "4160,924.79" "1" "1" "0")
(command "_insert" "blkuc13" "4160,924.42" "1" "1" "180")
(command "_insert" "blkuc13" "4160,925.16" "1" "1" "0")
(command "_insert" "blkuc13" "4160,924.79" "1" "1" "180")
(command "_insert" "blkuc13" "4160,925.53" "1" "1" "0")
(command "_insert" "blkuc13" "4160,925.16" "1" "1" "180")
(command "_insert" "blkuc13" "4160,925.9" "1" "1" "0")
(command "_insert" "blkuc13" "4160,925.53" "1" "1" "180")
(command "_insert" "blkuc13" "4160,926.27" "1" "1" "0")
(command "_insert" "blkuc13" "4160,925.9" "1" "1" "180")
(command "_insert" "blkuc13" "4160,926.64" "1" "1" "0")
(command "_insert" "blkuc13" "4160,926.27" "1" "1" "180")
(command "_insert" "blkuc13" "4160,927.01" "1" "1" "0")
(command "_insert" "blkuc13" "4160,926.64" "1" "1" "180")
(command "_insert" "blkuc13" "4160,927.38" "1" "1" "0")
(command "_insert" "blkuc13" "4160,927.01" "1" "1" "180")
(command "_insert" "blkuc13" "4160,927.75" "1" "1" "0")
(command "_insert" "blkuc13" "4160,927.38" "1" "1" "180")
(command "_layer" "set" "phccover" "")
(command "_rectangle" "4158.866,933.3" "4161.134,866.7")
(command "_layer" "set" "nitride" "")
(setq phc13 currobj)
(command "_layer" "set" "cover" "")
(command "_rectangle" "4158.866,836.7" "4161.134,963.3")
(command "_layer" "set" "nitride" "")
(command "_layer" "set" "text" "")
(command "_circle" "4157.916,846.7" "0.075")
(command "_circle" "4157.541,846.7" "0.15")
(command "_circle" "4157.166,846.7" "0.075")
(command "_circle" "4156.791,846.7" "0.15")
(command "_circle" "4157.916,848.7" "0.075")
(command "_circle" "4157.541,848.7" "0.075")
(command "_circle" "4157.166,848.7" "0.15")
(command "_circle" "4156.791,848.7" "0.15")
(command "_circle" "4157.916,850.7" "0.075")
(command "_circle" "4157.541,850.7" "0.15")
(command "_circle" "4157.166,850.7" "0.15")
(command "_circle" "4156.791,850.7" "0.15")
(command "_circle" "4157.916,852.7" "0.075")
(command "_circle" "4157.541,852.7" "0.075")
(command "_circle" "4157.166,852.7" "0.075")
(command "_circle" "4156.791,852.7" "0.075")
(command "_circle" "4156.416,852.7" "0.15")
(command "_circle" "4157.916,854.7" "0.075")
(command "_circle" "4157.541,854.7" "0.15")
(command "_circle" "4157.166,854.7" "0.075")
(command "_circle" "4156.791,854.7" "0.075")
(command "_circle" "4156.416,854.7" "0.15")
(command "_circle" "4157.916,856.7" "0.075")
(command "_circle" "4157.541,856.7" "0.075")
(command "_circle" "4157.166,856.7" "0.15")
(command "_circle" "4156.791,856.7" "0.075")
(command "_circle" "4156.416,856.7" "0.15")
(command "_circle" "4157.916,858.7" "0.075")
(command "_circle" "4157.541,858.7" "0.15")
(command "_circle" "4157.166,858.7" "0.15")
(command "_circle" "4156.791,858.7" "0.075")
(command "_circle" "4156.416,858.7" "0.15")
(command "_circle" "4157.916,860.7" "0.075")
(command "_circle" "4157.541,860.7" "0.075")
(command "_circle" "4157.166,860.7" "0.075")
(command "_circle" "4156.791,860.7" "0.15")
(command "_circle" "4156.416,860.7" "0.15")
(command "_circle" "4157.916,862.7" "0.075")
(command "_circle" "4157.541,862.7" "0.15")
(command "_circle" "4157.166,862.7" "0.075")
(command "_circle" "4156.791,862.7" "0.15")
(command "_circle" "4156.416,862.7" "0.15")
(command "_circle" "4157.916,864.7" "0.075")
(command "_circle" "4157.541,864.7" "0.075")
(command "_circle" "4157.166,864.7" "0.15")
(command "_circle" "4156.791,864.7" "0.15")
(command "_circle" "4156.416,864.7" "0.15")
(command "_circle" "4157.916,866.7" "0.075")
(command "_circle" "4157.541,866.7" "0.15")
(command "_circle" "4157.166,866.7" "0.15")
(command "_circle" "4156.791,866.7" "0.15")
(command "_circle" "4156.416,866.7" "0.15")
(command "_circle" "4157.916,868.7" "0.075")
(command "_circle" "4157.541,868.7" "0.075")
(command "_circle" "4157.166,868.7" "0.075")
(command "_circle" "4156.791,868.7" "0.075")
(command "_circle" "4156.416,868.7" "0.075")
(command "_circle" "4156.041,868.7" "0.15")
(command "_circle" "4157.916,870.7" "0.075")
(command "_circle" "4157.541,870.7" "0.15")
(command "_circle" "4157.166,870.7" "0.075")
(command "_circle" "4156.791,870.7" "0.075")
(command "_circle" "4156.416,870.7" "0.075")
(command "_circle" "4156.041,870.7" "0.15")
(command "_circle" "4157.916,872.7" "0.075")
(command "_circle" "4157.541,872.7" "0.075")
(command "_circle" "4157.166,872.7" "0.15")
(command "_circle" "4156.791,872.7" "0.075")
(command "_circle" "4156.416,872.7" "0.075")
(command "_circle" "4156.041,872.7" "0.15")
(command "_circle" "4157.916,874.7" "0.075")
(command "_circle" "4157.541,874.7" "0.15")
(command "_circle" "4157.166,874.7" "0.15")
(command "_circle" "4156.791,874.7" "0.075")
(command "_circle" "4156.416,874.7" "0.075")
(command "_circle" "4156.041,874.7" "0.15")
(command "_circle" "4157.916,876.7" "0.075")
(command "_circle" "4157.541,876.7" "0.075")
(command "_circle" "4157.166,876.7" "0.075")
(command "_circle" "4156.791,876.7" "0.15")
(command "_circle" "4156.416,876.7" "0.075")
(command "_circle" "4156.041,876.7" "0.15")
(command "_circle" "4157.916,878.7" "0.075")
(command "_circle" "4157.541,878.7" "0.15")
(command "_circle" "4157.166,878.7" "0.075")
(command "_circle" "4156.791,878.7" "0.15")
(command "_circle" "4156.416,878.7" "0.075")
(command "_circle" "4156.041,878.7" "0.15")
(command "_circle" "4157.916,880.7" "0.075")
(command "_circle" "4157.541,880.7" "0.075")
(command "_circle" "4157.166,880.7" "0.15")
(command "_circle" "4156.791,880.7" "0.15")
(command "_circle" "4156.416,880.7" "0.075")
(command "_circle" "4156.041,880.7" "0.15")
(command "_circle" "4157.916,882.7" "0.075")
(command "_circle" "4157.541,882.7" "0.15")
(command "_circle" "4157.166,882.7" "0.15")
(command "_circle" "4156.791,882.7" "0.15")
(command "_circle" "4156.416,882.7" "0.075")
(command "_circle" "4156.041,882.7" "0.15")
(command "_circle" "4157.916,884.7" "0.075")
(command "_circle" "4157.541,884.7" "0.075")
(command "_circle" "4157.166,884.7" "0.075")
(command "_circle" "4156.791,884.7" "0.075")
(command "_circle" "4156.416,884.7" "0.15")
(command "_circle" "4156.041,884.7" "0.15")
(command "_circle" "4157.916,886.7" "0.075")
(command "_circle" "4157.541,886.7" "0.15")
(command "_circle" "4157.166,886.7" "0.075")
(command "_circle" "4156.791,886.7" "0.075")
(command "_circle" "4156.416,886.7" "0.15")
(command "_circle" "4156.041,886.7" "0.15")
(command "_circle" "4157.916,888.7" "0.075")
(command "_circle" "4157.541,888.7" "0.075")
(command "_circle" "4157.166,888.7" "0.15")
(command "_circle" "4156.791,888.7" "0.075")
(command "_circle" "4156.416,888.7" "0.15")
(command "_circle" "4156.041,888.7" "0.15")
(command "_circle" "4157.916,890.7" "0.075")
(command "_circle" "4157.541,890.7" "0.15")
(command "_circle" "4157.166,890.7" "0.15")
(command "_circle" "4156.791,890.7" "0.075")
(command "_circle" "4156.416,890.7" "0.15")
(command "_circle" "4156.041,890.7" "0.15")
(command "_circle" "4157.916,892.7" "0.075")
(command "_circle" "4157.541,892.7" "0.075")
(command "_circle" "4157.166,892.7" "0.075")
(command "_circle" "4156.791,892.7" "0.15")
(command "_circle" "4156.416,892.7" "0.15")
(command "_circle" "4156.041,892.7" "0.15")
(command "_circle" "4157.916,894.7" "0.075")
(command "_circle" "4157.541,894.7" "0.15")
(command "_circle" "4157.166,894.7" "0.075")
(command "_circle" "4156.791,894.7" "0.15")
(command "_circle" "4156.416,894.7" "0.15")
(command "_circle" "4156.041,894.7" "0.15")
(command "_circle" "4157.916,896.7" "0.075")
(command "_circle" "4157.541,896.7" "0.075")
(command "_circle" "4157.166,896.7" "0.15")
(command "_circle" "4156.791,896.7" "0.15")
(command "_circle" "4156.416,896.7" "0.15")
(command "_circle" "4156.041,896.7" "0.15")
(command "_circle" "4157.916,898.7" "0.075")
(command "_circle" "4157.541,898.7" "0.15")
(command "_circle" "4157.166,898.7" "0.15")
(command "_circle" "4156.791,898.7" "0.15")
(command "_circle" "4156.416,898.7" "0.15")
(command "_circle" "4156.041,898.7" "0.15")
(command "_circle" "4157.916,900.7" "0.075")
(command "_circle" "4157.541,900.7" "0.075")
(command "_circle" "4157.166,900.7" "0.075")
(command "_circle" "4156.791,900.7" "0.075")
(command "_circle" "4156.416,900.7" "0.075")
(command "_circle" "4156.041,900.7" "0.075")
(command "_circle" "4155.666,900.7" "0.15")
(command "_circle" "4157.916,902.7" "0.075")
(command "_circle" "4157.541,902.7" "0.15")
(command "_circle" "4157.166,902.7" "0.075")
(command "_circle" "4156.791,902.7" "0.075")
(command "_circle" "4156.416,902.7" "0.075")
(command "_circle" "4156.041,902.7" "0.075")
(command "_circle" "4155.666,902.7" "0.15")
(command "_circle" "4157.916,904.7" "0.075")
(command "_circle" "4157.541,904.7" "0.075")
(command "_circle" "4157.166,904.7" "0.15")
(command "_circle" "4156.791,904.7" "0.075")
(command "_circle" "4156.416,904.7" "0.075")
(command "_circle" "4156.041,904.7" "0.075")
(command "_circle" "4155.666,904.7" "0.15")
(command "_circle" "4157.916,906.7" "0.075")
(command "_circle" "4157.541,906.7" "0.15")
(command "_circle" "4157.166,906.7" "0.15")
(command "_circle" "4156.791,906.7" "0.075")
(command "_circle" "4156.416,906.7" "0.075")
(command "_circle" "4156.041,906.7" "0.075")
(command "_circle" "4155.666,906.7" "0.15")
(command "_circle" "4157.916,908.7" "0.075")
(command "_circle" "4157.541,908.7" "0.075")
(command "_circle" "4157.166,908.7" "0.075")
(command "_circle" "4156.791,908.7" "0.15")
(command "_circle" "4156.416,908.7" "0.075")
(command "_circle" "4156.041,908.7" "0.075")
(command "_circle" "4155.666,908.7" "0.15")
(command "_circle" "4157.916,910.7" "0.075")
(command "_circle" "4157.541,910.7" "0.15")
(command "_circle" "4157.166,910.7" "0.075")
(command "_circle" "4156.791,910.7" "0.15")
(command "_circle" "4156.416,910.7" "0.075")
(command "_circle" "4156.041,910.7" "0.075")
(command "_circle" "4155.666,910.7" "0.15")
(command "_circle" "4157.916,912.7" "0.075")
(command "_circle" "4157.541,912.7" "0.075")
(command "_circle" "4157.166,912.7" "0.15")
(command "_circle" "4156.791,912.7" "0.15")
(command "_circle" "4156.416,912.7" "0.075")
(command "_circle" "4156.041,912.7" "0.075")
(command "_circle" "4155.666,912.7" "0.15")
(command "_circle" "4157.916,914.7" "0.075")
(command "_circle" "4157.541,914.7" "0.15")
(command "_circle" "4157.166,914.7" "0.15")
(command "_circle" "4156.791,914.7" "0.15")
(command "_circle" "4156.416,914.7" "0.075")
(command "_circle" "4156.041,914.7" "0.075")
(command "_circle" "4155.666,914.7" "0.15")
(command "_circle" "4157.916,916.7" "0.075")
(command "_circle" "4157.541,916.7" "0.075")
(command "_circle" "4157.166,916.7" "0.075")
(command "_circle" "4156.791,916.7" "0.075")
(command "_circle" "4156.416,916.7" "0.15")
(command "_circle" "4156.041,916.7" "0.075")
(command "_circle" "4155.666,916.7" "0.15")
(command "_circle" "4157.916,918.7" "0.075")
(command "_circle" "4157.541,918.7" "0.15")
(command "_circle" "4157.166,918.7" "0.075")
(command "_circle" "4156.791,918.7" "0.075")
(command "_circle" "4156.416,918.7" "0.15")
(command "_circle" "4156.041,918.7" "0.075")
(command "_circle" "4155.666,918.7" "0.15")
(command "_circle" "4157.916,920.7" "0.075")
(command "_circle" "4157.541,920.7" "0.075")
(command "_circle" "4157.166,920.7" "0.15")
(command "_circle" "4156.791,920.7" "0.075")
(command "_circle" "4156.416,920.7" "0.15")
(command "_circle" "4156.041,920.7" "0.075")
(command "_circle" "4155.666,920.7" "0.15")
(command "_circle" "4157.916,922.7" "0.075")
(command "_circle" "4157.541,922.7" "0.15")
(command "_circle" "4157.166,922.7" "0.15")
(command "_circle" "4156.791,922.7" "0.075")
(command "_circle" "4156.416,922.7" "0.15")
(command "_circle" "4156.041,922.7" "0.075")
(command "_circle" "4155.666,922.7" "0.15")
(command "_circle" "4157.916,924.7" "0.075")
(command "_circle" "4157.541,924.7" "0.075")
(command "_circle" "4157.166,924.7" "0.075")
(command "_circle" "4156.791,924.7" "0.15")
(command "_circle" "4156.416,924.7" "0.15")
(command "_circle" "4156.041,924.7" "0.075")
(command "_circle" "4155.666,924.7" "0.15")
(command "_circle" "4157.916,926.7" "0.075")
(command "_circle" "4157.541,926.7" "0.15")
(command "_circle" "4157.166,926.7" "0.075")
(command "_circle" "4156.791,926.7" "0.15")
(command "_circle" "4156.416,926.7" "0.15")
(command "_circle" "4156.041,926.7" "0.075")
(command "_circle" "4155.666,926.7" "0.15")
(command "_circle" "4157.916,928.7" "0.075")
(command "_circle" "4157.541,928.7" "0.075")
(command "_circle" "4157.166,928.7" "0.15")
(command "_circle" "4156.791,928.7" "0.15")
(command "_circle" "4156.416,928.7" "0.15")
(command "_circle" "4156.041,928.7" "0.075")
(command "_circle" "4155.666,928.7" "0.15")
(command "_circle" "4157.916,930.7" "0.075")
(command "_circle" "4157.541,930.7" "0.15")
(command "_circle" "4157.166,930.7" "0.15")
(command "_circle" "4156.791,930.7" "0.15")
(command "_circle" "4156.416,930.7" "0.15")
(command "_circle" "4156.041,930.7" "0.075")
(command "_circle" "4155.666,930.7" "0.15")
(command "_circle" "4157.916,932.7" "0.075")
(command "_circle" "4157.541,932.7" "0.075")
(command "_circle" "4157.166,932.7" "0.075")
(command "_circle" "4156.791,932.7" "0.075")
(command "_circle" "4156.416,932.7" "0.075")
(command "_circle" "4156.041,932.7" "0.15")
(command "_circle" "4155.666,932.7" "0.15")
(command "_circle" "4157.916,934.7" "0.075")
(command "_circle" "4157.541,934.7" "0.15")
(command "_circle" "4157.166,934.7" "0.075")
(command "_circle" "4156.791,934.7" "0.075")
(command "_circle" "4156.416,934.7" "0.075")
(command "_circle" "4156.041,934.7" "0.15")
(command "_circle" "4155.666,934.7" "0.15")
(command "_circle" "4157.916,936.7" "0.075")
(command "_circle" "4157.541,936.7" "0.075")
(command "_circle" "4157.166,936.7" "0.15")
(command "_circle" "4156.791,936.7" "0.075")
(command "_circle" "4156.416,936.7" "0.075")
(command "_circle" "4156.041,936.7" "0.15")
(command "_circle" "4155.666,936.7" "0.15")
(command "_circle" "4157.916,938.7" "0.075")
(command "_circle" "4157.541,938.7" "0.15")
(command "_circle" "4157.166,938.7" "0.15")
(command "_circle" "4156.791,938.7" "0.075")
(command "_circle" "4156.416,938.7" "0.075")
(command "_circle" "4156.041,938.7" "0.15")
(command "_circle" "4155.666,938.7" "0.15")
(command "_circle" "4157.916,940.7" "0.075")
(command "_circle" "4157.541,940.7" "0.075")
(command "_circle" "4157.166,940.7" "0.075")
(command "_circle" "4156.791,940.7" "0.15")
(command "_circle" "4156.416,940.7" "0.075")
(command "_circle" "4156.041,940.7" "0.15")
(command "_circle" "4155.666,940.7" "0.15")
(command "_circle" "4157.916,942.7" "0.075")
(command "_circle" "4157.541,942.7" "0.15")
(command "_circle" "4157.166,942.7" "0.075")
(command "_circle" "4156.791,942.7" "0.15")
(command "_circle" "4156.416,942.7" "0.075")
(command "_circle" "4156.041,942.7" "0.15")
(command "_circle" "4155.666,942.7" "0.15")
(command "_circle" "4157.916,944.7" "0.075")
(command "_circle" "4157.541,944.7" "0.075")
(command "_circle" "4157.166,944.7" "0.15")
(command "_circle" "4156.791,944.7" "0.15")
(command "_circle" "4156.416,944.7" "0.075")
(command "_circle" "4156.041,944.7" "0.15")
(command "_circle" "4155.666,944.7" "0.15")
(command "_circle" "4157.916,946.7" "0.075")
(command "_circle" "4157.541,946.7" "0.15")
(command "_circle" "4157.166,946.7" "0.15")
(command "_circle" "4156.791,946.7" "0.15")
(command "_circle" "4156.416,946.7" "0.075")
(command "_circle" "4156.041,946.7" "0.15")
(command "_circle" "4155.666,946.7" "0.15")
(command "_circle" "4157.916,948.7" "0.075")
(command "_circle" "4157.541,948.7" "0.075")
(command "_circle" "4157.166,948.7" "0.075")
(command "_circle" "4156.791,948.7" "0.075")
(command "_circle" "4156.416,948.7" "0.15")
(command "_circle" "4156.041,948.7" "0.15")
(command "_circle" "4155.666,948.7" "0.15")
(command "_circle" "4157.916,950.7" "0.075")
(command "_circle" "4157.541,950.7" "0.15")
(command "_circle" "4157.166,950.7" "0.075")
(command "_circle" "4156.791,950.7" "0.075")
(command "_circle" "4156.416,950.7" "0.15")
(command "_circle" "4156.041,950.7" "0.15")
(command "_circle" "4155.666,950.7" "0.15")
(command "_circle" "4157.916,952.7" "0.075")
(command "_circle" "4157.541,952.7" "0.075")
(command "_circle" "4157.166,952.7" "0.15")
(command "_circle" "4156.791,952.7" "0.075")
(command "_circle" "4156.416,952.7" "0.15")
(command "_circle" "4156.041,952.7" "0.15")
(command "_circle" "4155.666,952.7" "0.15")
(command "_circle" "4157.916,954.7" "0.075")
(command "_circle" "4157.541,954.7" "0.15")
(command "_circle" "4157.166,954.7" "0.15")
(command "_circle" "4156.791,954.7" "0.075")
(command "_circle" "4156.416,954.7" "0.15")
(command "_circle" "4156.041,954.7" "0.15")
(command "_circle" "4155.666,954.7" "0.15")
(command "_circle" "4157.916,956.7" "0.075")
(command "_circle" "4157.541,956.7" "0.075")
(command "_circle" "4157.166,956.7" "0.075")
(command "_circle" "4156.791,956.7" "0.15")
(command "_circle" "4156.416,956.7" "0.15")
(command "_circle" "4156.041,956.7" "0.15")
(command "_circle" "4155.666,956.7" "0.15")
(command "_circle" "4157.916,958.7" "0.075")
(command "_circle" "4157.541,958.7" "0.15")
(command "_circle" "4157.166,958.7" "0.075")
(command "_circle" "4156.791,958.7" "0.15")
(command "_circle" "4156.416,958.7" "0.15")
(command "_circle" "4156.041,958.7" "0.15")
(command "_circle" "4155.666,958.7" "0.15")
(command "_circle" "4157.916,960.7" "0.075")
(command "_circle" "4157.541,960.7" "0.075")
(command "_circle" "4157.166,960.7" "0.15")
(command "_circle" "4156.791,960.7" "0.15")
(command "_circle" "4156.416,960.7" "0.15")
(command "_circle" "4156.041,960.7" "0.15")
(command "_circle" "4155.666,960.7" "0.15")
(command "_circle" "4157.916,962.7" "0.075")
(command "_circle" "4157.541,962.7" "0.15")
(command "_circle" "4157.166,962.7" "0.15")
(command "_circle" "4156.791,962.7" "0.15")
(command "_circle" "4156.416,962.7" "0.15")
(command "_circle" "4156.041,962.7" "0.15")
(command "_circle" "4155.666,962.7" "0.15")
(command "_layer" "set" "nitride" "")
(command "_layer" "set" "text" "")
(command-s "_text" "4146.866,963.3" "2" "-90" "a = 370 nm" )
(sssetfirst nil (ssget "_L"))
(if (not (numberp (vl-string-search "Mac" (getvar "platform")))) (c:txtexp))
(command "_layer" "set" "nitride" "")
(command "_layer" "set" "text" "")
(command-s "_text" "4143.866,963.3" "2" "-90" "gap = 270 nm" )
(sssetfirst nil (ssget "_L"))
(if (not (numberp (vl-string-search "Mac" (getvar "platform")))) (c:txtexp))
(command "_layer" "set" "nitride" "")
(command "_layer" "set" "text" "")
(command-s "_text" "4140.866,963.3" "2" "-90" "amplitude = 134 nm" )
(sssetfirst nil (ssget "_L"))
(if (not (numberp (vl-string-search "Mac" (getvar "platform")))) (c:txtexp))
(command "_layer" "set" "nitride" "")
(command "_layer" "set" "text" "")
(command-s "_text" "4137.866,963.3" "2" "-90" "start width = 280 nm" )
(sssetfirst nil (ssget "_L"))
(if (not (numberp (vl-string-search "Mac" (getvar "platform")))) (c:txtexp))
(command "_layer" "set" "nitride" "")
(command "_layer" "set" "text" "")
(command-s "_text" "4134.866,963.3" "2" "-90" "width = 298 nm" )
(sssetfirst nil (ssget "_L"))
(if (not (numberp (vl-string-search "Mac" (getvar "platform")))) (c:txtexp))
(command "_layer" "set" "nitride" "")
(command "_layer" "set" "text" "")
(command-s "_text" "4131.866,963.3" "2" "-90" "taper: 15" )
(sssetfirst nil (ssget "_L"))
(if (not (numberp (vl-string-search "Mac" (getvar "platform")))) (c:txtexp))
(command "_layer" "set" "nitride" "")
(command "_layer" "set" "text" "")
(command-s "_text" "4128.866,963.3" "2" "-90" "nominal: 150" )
(sssetfirst nil (ssget "_L"))
(if (not (numberp (vl-string-search "Mac" (getvar "platform")))) (c:txtexp))
(command "_layer" "set" "nitride" "")
(command "_layer" "set" "indicators" "")
(setq coords (list 
(list 4080.415 940) 
(list 4080.415 920) 
(list 4060.415 900) 
(list 4080.415 880) 
(list 4080.415 860) 
(list 4080.415 900) 
(list 4080.415 887.0711) 
(list 4067.4861 900) 
(list 4080.415 912.9289) 
(list 4080.415 900)))
(apply 'command (append '("pline") coords '("c")))
(command "._fillet" "radius" "1" "._fillet" "P" (entlast))
(setq coords (list 
(list 4239.585 940) 
(list 4239.585 920) 
(list 4259.585 900) 
(list 4239.585 880) 
(list 4239.585 860) 
(list 4239.585 900) 
(list 4239.585 887.0711) 
(list 4252.5139 900) 
(list 4239.585 912.9289) 
(list 4239.585 900)))
(apply 'command (append '("pline") coords '("c")))
(command "._fillet" "radius" "1" "._fillet" "P" (entlast))
(command "_layer" "set" "holes" "")
(command "_circle" "4078.0629,914.1124" "0.5")
(command "_circle" "4075.7109,911.7603" "0.5")
(command "_circle" "4073.3588,909.4083" "0.5")
(command "_circle" "4071.0067,907.0562" "0.5")
(command "_circle" "4068.6547,904.7041" "0.5")
(command "_circle" "4066.3026,902.3521" "0.5")
(command "_circle" "4063.9505,900" "0.5")
(command "_circle" "4066.3026,897.6479" "0.5")
(command "_circle" "4068.6547,895.2959" "0.5")
(command "_circle" "4071.0067,892.9438" "0.5")
(command "_circle" "4073.3588,890.5917" "0.5")
(command "_circle" "4075.7109,888.2397" "0.5")
(command "_circle" "4078.0629,885.8876" "0.5")
(command "_circle" "4241.9371,914.1124" "0.5")
(command "_circle" "4244.2891,911.7603" "0.5")
(command "_circle" "4246.6412,909.4083" "0.5")
(command "_circle" "4248.9933,907.0562" "0.5")
(command "_circle" "4251.3453,904.7041" "0.5")
(command "_circle" "4253.6974,902.3521" "0.5")
(command "_circle" "4256.0495,900" "0.5")
(command "_circle" "4253.6974,897.6479" "0.5")
(command "_circle" "4251.3453,895.2959" "0.5")
(command "_circle" "4248.9933,892.9438" "0.5")
(command "_circle" "4246.6412,890.5917" "0.5")
(command "_circle" "4244.2891,888.2397" "0.5")
(command "_circle" "4241.9371,885.8876" "0.5")
(command "_layer" "set" "nitride" "")
(command "_block" "blkcoupler13" "4160,900" coupler13 "")
(command "_insert" "blkcoupler13" "4160,900" "1" "1" "0")
(command "_insert" "blkcoupler13" "4160,900" "1" "1" "180")
(command "_block" "blksinglenanobeam13" "4160,900" singlenanobeam13 "")
(command "_insert" "blksinglenanobeam13" "4160,900" "1" "1" "0")
(command "_insert" "blksinglenanobeam13" "4160,900" "1" "1" "180")
(command "_block" "blkanglednodearray13" "4160,900" anglednodearray13 "")
(command "_insert" "blkanglednodearray13" "4160,900" "1" "1" "0")
(command "_insert" "blkanglednodearray13" "4160,900" "1" "1" "180")
(command "_block" "blkcooledsinglenanobeam13" "4160,900" cooledsinglenanobeam13 "")
(command "_insert" "blkcooledsinglenanobeam13" "4160,900" "1" "1" "0")
(command "_insert" "blkcooledsinglenanobeam13" "4160,900" "1" "1" "180")
(command "_block" "blkyjunction13" "4160,900" yjunction13 "")
(command "_insert" "blkyjunction13" "4160,900" "1" "1" "0")
(command "_insert" "blkyjunction13" "4160,900" "1" "1" "180")
; DRAWING BULGING VEE GROOVE
(command "_layer" "set" "vgroove" "")
(setq coords (list 
(list 4085.415 -605) 
(list 4085.415 0) 
(list 4085.415 0) 
(list 4085.415 1800) 
(list 4085.415 1800) 
(list 4085.415 2405) 
(list 4234.585 2405) 
(list 4234.585 1800) 
(list 4234.585 1800) 
(list 4234.585 0) 
(list 4234.585 0) 
(list 4234.585 -605)))
(apply 'command (append '("pline") coords '("c")))
(command "._fillet" "radius" "0" "._fillet" "P" (entlast))
(command "_layer" "set" "window" "")
(command "_rectangle" "4085.415,-1935" "4234.585,-600")
(command "_rectangle" "4085.415,2400" "4234.585,5300")
(command "_layer" "set" "grid" "")
(command "_rectangle" "4086.415,-1934" "4109.9433,-1909.2133")
(command "_array" "last" "" "R" "75" "3" "25.7867" "24.5283")
(command "_rectangle" "4161,-1934" "4184.5283,-1909.2133")
(command "_array" "last" "" "R" "75" "3" "25.7867" "24.5283")
(command "_rectangle" "4086.415,1" "4109.9433,25.7")
(command "_array" "last" "" "R" "70" "3" "25.7" "24.5283")
(command "_rectangle" "4161,1" "4184.5283,25.7")
(command "_array" "last" "" "R" "70" "3" "25.7" "24.5283")
(command "_rectangle" "4086.415,1801" "4109.9433,1825.9185")
(command "_array" "last" "" "R" "135" "3" "25.9185" "24.5283")
(command "_rectangle" "4161,1801" "4184.5283,1825.9185")
(command "_array" "last" "" "R" "135" "3" "25.9185" "24.5283")
(command "_layer" "set" "vgrooveFDA" "")
(command "_rectangle" "4234.585,-2233" "4085.415,-1933")
(command "_layer" "set" "nitride" "")
(command "_layer" "set" "holes" "")
(command "_circle" "4237.085,331.5" "0.5")
(command "_array" "last" "" "R" "379" "1" "3" "2.5")
(command "_circle" "4082.915,331.5" "0.5")
(command "_array" "last" "" "R" "379" "1" "3" "-2.5")
(command "_layer" "set" "nitride" "")
(command "_layer" "set" "window" "")
(command "_layer" "set" "window" "")
(command "_rectangle" "4239.585,0" "4400.415,1800")
(command "._fillet" "radius" "20" "._fillet" "P" (entlast))
(command "_layer" "set" "grid" "")
(command "_rectangle" "4240.585,1" "4262.4179,25.7")
(command "_array" "last" "" "R" "70" "7" "25.7" "22.8329")
(command "_layer" "set" "nitride" "")
; DRAWING REGION LAYER
(command "_layer" "set" "regionLayer13" "")
(command "_rectangle" "4080,-460" "4240,2260")
(command "_layer" "set" "nitride" "")
(setq coupler13 nil)
(setq singlenanobeam13 nil)
(setq anglednodearray13 nil)
(setq cooledsinglenanobeam13 nil)
(setq yjunction13 nil)
; DEVICE #14
(command "_layer" "set" "window" "")
(command "_circle" "4392.915,-415" "5")
(command "_circle" "4392.915,-402.5" "5")
(command "_circle" "4392.915,-390" "5")
(command "_circle" "4392.915,-377.5" "5")
(command "_circle" "4380.415,-415" "5")
(command "_circle" "4380.415,-402.5" "5")
(command "_circle" "4380.415,-390" "5")
(command "_circle" "4380.415,-377.5" "5")
(command "_circle" "4367.915,-415" "5")
(command "_circle" "4367.915,-402.5" "5")
(command "_circle" "4367.915,-390" "5")
(command "_circle" "4367.915,-377.5" "5")
(command "_circle" "4355.415,-415" "5")
(command "_circle" "4355.415,-402.5" "5")
(command "_layer" "set" "nitride" "")
(setq currobj nil)
(setq currobj (ssadd))
; DRAWING COUPLER
(setq coords (list 
(list 4480.0645 -415) 
(list 4480.0645 -413) 
(list 4553.585 -413) 
(list 4553.585 -413) 
(list 4553.9677 -413.0761) 
(list 4554.2921 -413.2929) 
(list 4554.5089 -413.6173) 
(list 4554.585 -414) 
(list 4554.585 -411.8) 
(list 4554.585 -411.8) 
(list 4554.5089 -412.1827) 
(list 4554.2921 -412.5071) 
(list 4553.9677 -412.7239) 
(list 4553.585 -412.8) 
(list 4480.0645 -412.8) 
(list 4480.0645 -410.8) 
(list 4479.9355 -410.8) 
(list 4479.9355 -412.8) 
(list 4406.415 -412.8) 
(list 4406.0323 -412.7239) 
(list 4405.7079 -412.5071) 
(list 4405.4911 -412.1827) 
(list 4405.415 -411.8) 
(list 4405.415 -411.8) 
(list 4405.415 -414) 
(list 4405.4911 -413.6173) 
(list 4405.7079 -413.2929) 
(list 4406.0323 -413.0761) 
(list 4406.415 -413) 
(list 4406.415 -413) 
(list 4479.9355 -413) 
(list 4479.9355 -415)))
(apply 'command (append '("pline") coords '("c")))
(setq currobj (ssadd (entlast) currobj))
(command "._fillet" "radius" "0.3" "._fillet" "P" (entlast))
(command "_layer" "set" "holes" "")
(command "_circle" "4480,-412.9" "0.113")
(setq currobj (ssadd (entlast) currobj))
(command "_layer" "set" "nitride" "")
(command "_layer" "set" "text" "")
(command "_circle" "4479.2,-415" "0.075")
(command "_circle" "4479.2,-414.7" "0.075")
(command "_circle" "4479.2,-414.4" "0.075")
(command "_circle" "4478.9,-415" "0.075")
(command "_circle" "4478.9,-414.7" "0.075")
(command "_circle" "4478.9,-414.4" "0.075")
(command "_circle" "4478.6,-415" "0.075")
(command "_circle" "4478.6,-414.7" "0.075")
(command "_circle" "4478.6,-414.4" "0.075")
(command "_layer" "set" "nitride" "")
(command "_layer" "set" "prebias" "")
(command "_rectangle" "4405.415,-414" "4554.585,-411.8")
(setq currobj (ssadd (entlast) currobj))
(command "_rectangle" "4479.9355,-415" "4480.0645,-410.8")
(setq currobj (ssadd (entlast) currobj))
(command "_layer" "set" "nitride" "")
(setq coupler14 currobj)
(setq currobj nil)
(setq currobj (ssadd))
; DRAWING SINGLE NANOBEAM
(setq coords (list 
(list 4480.0645 -410.8) 
(list 4480.0645 -409.1417) 
(list 4480.0645 -407.4833) 
(list 4480.0645 -405.825) 
(list 4480.0645 -404.1667) 
(list 4480.0645 -402.5083) 
(list 4480.0645 -400.85) 
(list 4480.0645 -399.1917) 
(list 4480.0645 -397.5333) 
(list 4480.0646 -395.875) 
(list 4480.0646 -394.2167) 
(list 4480.0646 -392.5583) 
(list 4480.0646 -390.9) 
(list 4480.0647 -389.2417) 
(list 4480.0647 -387.5833) 
(list 4480.0647 -385.925) 
(list 4480.0648 -384.2667) 
(list 4480.0648 -382.6083) 
(list 4480.0649 -380.95) 
(list 4480.065 -379.2917) 
(list 4480.0651 -377.6333) 
(list 4480.0651 -375.975) 
(list 4480.0652 -374.3167) 
(list 4480.0653 -372.6583) 
(list 4480.0655 -371) 
(list 4480.0656 -369.3417) 
(list 4480.0657 -367.6833) 
(list 4480.0659 -366.025) 
(list 4480.066 -364.3667) 
(list 4480.0662 -362.7083) 
(list 4480.0664 -361.05) 
(list 4480.0666 -359.3917) 
(list 4480.0668 -357.7333) 
(list 4480.067 -356.075) 
(list 4480.0672 -354.4167) 
(list 4480.0675 -352.7583) 
(list 4480.0678 -351.1) 
(list 4480.068 -349.4417) 
(list 4480.0683 -347.7833) 
(list 4480.0686 -346.125) 
(list 4480.069 -344.4667) 
(list 4480.0693 -342.8083) 
(list 4480.0697 -341.15) 
(list 4480.07 -339.4917) 
(list 4480.0704 -337.8333) 
(list 4480.0709 -336.175) 
(list 4480.0713 -334.5167) 
(list 4480.0717 -332.8583) 
(list 4480.0722 -331.2) 
(list 4480.0727 -329.5417) 
(list 4480.0732 -327.8833) 
(list 4480.0737 -326.225) 
(list 4480.0743 -324.5667) 
(list 4480.0749 -322.9083) 
(list 4480.0755 -321.25) 
(list 4480.0761 -319.5917) 
(list 4480.0767 -317.9333) 
(list 4480.0774 -316.275) 
(list 4480.0781 -314.6167) 
(list 4480.0788 -312.9583) 
(list 4480.0796 -311.3) 
(list 4480.0803 -309.6417) 
(list 4480.0811 -307.9833) 
(list 4480.0819 -306.325) 
(list 4480.0828 -304.6667) 
(list 4480.0837 -303.0083) 
(list 4480.0845 -301.35) 
(list 4480.0855 -299.6917) 
(list 4480.0864 -298.0333) 
(list 4480.0874 -296.375) 
(list 4480.0884 -294.7167) 
(list 4480.0895 -293.0583) 
(list 4480.0905 -291.4) 
(list 4480.0916 -289.7417) 
(list 4480.0928 -288.0833) 
(list 4480.0939 -286.425) 
(list 4480.0951 -284.7667) 
(list 4480.0963 -283.1083) 
(list 4480.0976 -281.45) 
(list 4480.0989 -279.7917) 
(list 4480.1002 -278.1333) 
(list 4480.1016 -276.475) 
(list 4480.1029 -274.8167) 
(list 4480.1044 -273.1583) 
(list 4480.1058 -271.5) 
(list 4480.1073 -269.8417) 
(list 4480.1089 -268.1833) 
(list 4480.1104 -266.525) 
(list 4480.112 -264.8667) 
(list 4480.1137 -263.2083) 
(list 4480.1153 -261.55) 
(list 4480.117 -259.8917) 
(list 4480.1188 -258.2333) 
(list 4480.1206 -256.575) 
(list 4480.1224 -254.9167) 
(list 4480.1243 -253.2583) 
(list 4480.1262 -251.6) 
(list 4480.1281 -249.9417) 
(list 4480.1301 -248.2833) 
(list 4480.1322 -246.625) 
(list 4480.1342 -244.9667) 
(list 4480.1363 -243.3083) 
(list 4480.1385 -241.65) 
(list 4480.1407 -239.9917) 
(list 4480.1429 -238.3333) 
(list 4480.1452 -236.675) 
(list 4480.1476 -235.0167) 
(list 4480.1499 -233.3583) 
(list 4480.1523 -231.7) 
(list 4480.1548 -230.0417) 
(list 4480.1573 -228.3833) 
(list 4480.1599 -226.725) 
(list 4480.1625 -225.0667) 
(list 4480.1651 -223.4083) 
(list 4480.1678 -221.75) 
(list 4480.1706 -220.0917) 
(list 4480.1733 -218.4333) 
(list 4480.1762 -216.775) 
(list 4480.1791 -215.1167) 
(list 4480.182 -213.4583) 
(list 4480.185 -211.8) 
(list 4479.815 -211.8) 
(list 4479.818 -213.4583) 
(list 4479.8209 -215.1167) 
(list 4479.8238 -216.775) 
(list 4479.8267 -218.4333) 
(list 4479.8294 -220.0917) 
(list 4479.8322 -221.75) 
(list 4479.8349 -223.4083) 
(list 4479.8375 -225.0667) 
(list 4479.8401 -226.725) 
(list 4479.8427 -228.3833) 
(list 4479.8452 -230.0417) 
(list 4479.8477 -231.7) 
(list 4479.8501 -233.3583) 
(list 4479.8524 -235.0167) 
(list 4479.8548 -236.675) 
(list 4479.8571 -238.3333) 
(list 4479.8593 -239.9917) 
(list 4479.8615 -241.65) 
(list 4479.8637 -243.3083) 
(list 4479.8658 -244.9667) 
(list 4479.8678 -246.625) 
(list 4479.8699 -248.2833) 
(list 4479.8719 -249.9417) 
(list 4479.8738 -251.6) 
(list 4479.8757 -253.2583) 
(list 4479.8776 -254.9167) 
(list 4479.8794 -256.575) 
(list 4479.8812 -258.2333) 
(list 4479.883 -259.8917) 
(list 4479.8847 -261.55) 
(list 4479.8863 -263.2083) 
(list 4479.888 -264.8667) 
(list 4479.8896 -266.525) 
(list 4479.8911 -268.1833) 
(list 4479.8927 -269.8417) 
(list 4479.8942 -271.5) 
(list 4479.8956 -273.1583) 
(list 4479.8971 -274.8167) 
(list 4479.8984 -276.475) 
(list 4479.8998 -278.1333) 
(list 4479.9011 -279.7917) 
(list 4479.9024 -281.45) 
(list 4479.9037 -283.1083) 
(list 4479.9049 -284.7667) 
(list 4479.9061 -286.425) 
(list 4479.9072 -288.0833) 
(list 4479.9084 -289.7417) 
(list 4479.9095 -291.4) 
(list 4479.9105 -293.0583) 
(list 4479.9116 -294.7167) 
(list 4479.9126 -296.375) 
(list 4479.9136 -298.0333) 
(list 4479.9145 -299.6917) 
(list 4479.9155 -301.35) 
(list 4479.9163 -303.0083) 
(list 4479.9172 -304.6667) 
(list 4479.9181 -306.325) 
(list 4479.9189 -307.9833) 
(list 4479.9197 -309.6417) 
(list 4479.9204 -311.3) 
(list 4479.9212 -312.9583) 
(list 4479.9219 -314.6167) 
(list 4479.9226 -316.275) 
(list 4479.9233 -317.9333) 
(list 4479.9239 -319.5917) 
(list 4479.9245 -321.25) 
(list 4479.9251 -322.9083) 
(list 4479.9257 -324.5667) 
(list 4479.9263 -326.225) 
(list 4479.9268 -327.8833) 
(list 4479.9273 -329.5417) 
(list 4479.9278 -331.2) 
(list 4479.9283 -332.8583) 
(list 4479.9287 -334.5167) 
(list 4479.9291 -336.175) 
(list 4479.9296 -337.8333) 
(list 4479.93 -339.4917) 
(list 4479.9303 -341.15) 
(list 4479.9307 -342.8083) 
(list 4479.931 -344.4667) 
(list 4479.9314 -346.125) 
(list 4479.9317 -347.7833) 
(list 4479.932 -349.4417) 
(list 4479.9322 -351.1) 
(list 4479.9325 -352.7583) 
(list 4479.9328 -354.4167) 
(list 4479.933 -356.075) 
(list 4479.9332 -357.7333) 
(list 4479.9334 -359.3917) 
(list 4479.9336 -361.05) 
(list 4479.9338 -362.7083) 
(list 4479.934 -364.3667) 
(list 4479.9341 -366.025) 
(list 4479.9343 -367.6833) 
(list 4479.9344 -369.3417) 
(list 4479.9345 -371) 
(list 4479.9347 -372.6583) 
(list 4479.9348 -374.3167) 
(list 4479.9349 -375.975) 
(list 4479.9349 -377.6333) 
(list 4479.935 -379.2917) 
(list 4479.9351 -380.95) 
(list 4479.9352 -382.6083) 
(list 4479.9352 -384.2667) 
(list 4479.9353 -385.925) 
(list 4479.9353 -387.5833) 
(list 4479.9353 -389.2417) 
(list 4479.9354 -390.9) 
(list 4479.9354 -392.5583) 
(list 4479.9354 -394.2167) 
(list 4479.9354 -395.875) 
(list 4479.9355 -397.5333) 
(list 4479.9355 -399.1917) 
(list 4479.9355 -400.85) 
(list 4479.9355 -402.5083) 
(list 4479.9355 -404.1667) 
(list 4479.9355 -405.825) 
(list 4479.9355 -407.4833) 
(list 4479.9355 -409.1417) 
(list 4479.9355 -410.8)))
(apply 'command (append '("pline") coords '("c")))
(setq currobj (ssadd (entlast) currobj))
(command "_layer" "set" "prebias" "")
(command "_rectangle" "4479.815,-410.8" "4480.185,-211.8")
(setq currobj (ssadd (entlast) currobj))
(command "_layer" "set" "nitride" "")
(setq singlenanobeam14 currobj)
(setq currobj nil)
(setq currobj (ssadd))
; DRAWING NODE ARRAY
(setq coords (list 
(list 4480.185 -211.8) 
(list 4480.5625 -201.8) 
(list 4480.5625 -201.8) 
(list 4480.5625 -200.8) 
(list 4554.585 -212.6864) 
(list 4554.585 -207.7434) 
(list 4480.5625 -197.357) 
(list 4480.5625 -196.357) 
(list 4480.5625 -196.357) 
(list 4480.2625 -186.357) 
(list 4479.7375 -186.357) 
(list 4479.4375 -196.357) 
(list 4479.4375 -196.357) 
(list 4479.4375 -197.357) 
(list 4405.415 -207.7434) 
(list 4405.415 -212.6864) 
(list 4479.4375 -200.8) 
(list 4479.4375 -201.8) 
(list 4479.4375 -201.8) 
(list 4479.815 -211.8)))
(apply 'command (append '("pline") coords '("c")))
(setq currobj (ssadd (entlast) currobj))
(command "_layer" "set" "prebias" "")
(setq coords (list 
(list 4479.4375 -212.6864) 
(list 4479.4375 -200.8) 
(list 4405.415 -212.6864) 
(list 4405.415 -207.7434) 
(list 4479.4375 -197.357) 
(list 4479.4375 -186.357) 
(list 4480.5625 -186.357) 
(list 4480.5625 -197.357) 
(list 4554.585 -207.7434) 
(list 4554.585 -212.6864) 
(list 4480.5625 -200.8) 
(list 4480.5625 -212.6864)))
(apply 'command (append '("pline") coords '("c")))
(setq currobj (ssadd (entlast) currobj))
(command "_layer" "set" "nitride" "")
(command "_layer" "set" "fda1" "")
(setq coords (list 
(list 4480.5625 -200.657) 
(list 4554.585 -212.5434) 
(list 4554.585 -212.3664) 
(list 4480.5625 -200.58)))
(apply 'command (append '("pline") coords '("c")))
(setq currobj (ssadd (entlast) currobj))
(setq coords (list 
(list 4480.5625 -200.437) 
(list 4554.585 -212.2234) 
(list 4554.585 -212.0464) 
(list 4480.5625 -200.36)))
(apply 'command (append '("pline") coords '("c")))
(setq currobj (ssadd (entlast) currobj))
(setq coords (list 
(list 4480.5625 -200.217) 
(list 4554.585 -211.9034) 
(list 4554.585 -211.7264) 
(list 4480.5625 -200.14)))
(apply 'command (append '("pline") coords '("c")))
(setq currobj (ssadd (entlast) currobj))
(setq coords (list 
(list 4480.5625 -199.997) 
(list 4554.585 -211.5834) 
(list 4554.585 -211.4064) 
(list 4480.5625 -199.92)))
(apply 'command (append '("pline") coords '("c")))
(setq currobj (ssadd (entlast) currobj))
(setq coords (list 
(list 4480.5625 -199.777) 
(list 4554.585 -211.2634) 
(list 4554.585 -211.0864) 
(list 4480.5625 -199.7)))
(apply 'command (append '("pline") coords '("c")))
(setq currobj (ssadd (entlast) currobj))
(setq coords (list 
(list 4480.5625 -199.557) 
(list 4554.585 -210.9434) 
(list 4554.585 -210.7664) 
(list 4480.5625 -199.48)))
(apply 'command (append '("pline") coords '("c")))
(setq currobj (ssadd (entlast) currobj))
(setq coords (list 
(list 4480.5625 -199.337) 
(list 4554.585 -210.6234) 
(list 4554.585 -210.4464) 
(list 4480.5625 -199.26)))
(apply 'command (append '("pline") coords '("c")))
(setq currobj (ssadd (entlast) currobj))
(setq coords (list 
(list 4480.5625 -199.117) 
(list 4554.585 -210.3034) 
(list 4554.585 -210.1264) 
(list 4480.5625 -199.04)))
(apply 'command (append '("pline") coords '("c")))
(setq currobj (ssadd (entlast) currobj))
(setq coords (list 
(list 4480.5625 -198.897) 
(list 4554.585 -209.9834) 
(list 4554.585 -209.8064) 
(list 4480.5625 -198.82)))
(apply 'command (append '("pline") coords '("c")))
(setq currobj (ssadd (entlast) currobj))
(setq coords (list 
(list 4480.5625 -198.677) 
(list 4554.585 -209.6634) 
(list 4554.585 -209.4864) 
(list 4480.5625 -198.6)))
(apply 'command (append '("pline") coords '("c")))
(setq currobj (ssadd (entlast) currobj))
(setq coords (list 
(list 4480.5625 -198.457) 
(list 4554.585 -209.3434) 
(list 4554.585 -209.1664) 
(list 4480.5625 -198.38)))
(apply 'command (append '("pline") coords '("c")))
(setq currobj (ssadd (entlast) currobj))
(setq coords (list 
(list 4480.5625 -198.237) 
(list 4554.585 -209.0234) 
(list 4554.585 -208.8464) 
(list 4480.5625 -198.16)))
(apply 'command (append '("pline") coords '("c")))
(setq currobj (ssadd (entlast) currobj))
(setq coords (list 
(list 4480.5625 -198.017) 
(list 4554.585 -208.7034) 
(list 4554.585 -208.5264) 
(list 4480.5625 -197.94)))
(apply 'command (append '("pline") coords '("c")))
(setq currobj (ssadd (entlast) currobj))
(setq coords (list 
(list 4480.5625 -197.797) 
(list 4554.585 -208.3834) 
(list 4554.585 -208.2064) 
(list 4480.5625 -197.72)))
(apply 'command (append '("pline") coords '("c")))
(setq currobj (ssadd (entlast) currobj))
(setq coords (list 
(list 4480.5625 -197.577) 
(list 4554.585 -208.0634) 
(list 4554.585 -207.8864) 
(list 4480.5625 -197.5)))
(apply 'command (append '("pline") coords '("c")))
(setq currobj (ssadd (entlast) currobj))
(setq coords (list 
(list 4479.4375 -197.5) 
(list 4405.415 -207.8864) 
(list 4405.415 -208.0634) 
(list 4479.4375 -197.577)))
(apply 'command (append '("pline") coords '("c")))
(setq currobj (ssadd (entlast) currobj))
(setq coords (list 
(list 4479.4375 -197.72) 
(list 4405.415 -208.2064) 
(list 4405.415 -208.3834) 
(list 4479.4375 -197.797)))
(apply 'command (append '("pline") coords '("c")))
(setq currobj (ssadd (entlast) currobj))
(setq coords (list 
(list 4479.4375 -197.94) 
(list 4405.415 -208.5264) 
(list 4405.415 -208.7034) 
(list 4479.4375 -198.017)))
(apply 'command (append '("pline") coords '("c")))
(setq currobj (ssadd (entlast) currobj))
(setq coords (list 
(list 4479.4375 -198.16) 
(list 4405.415 -208.8464) 
(list 4405.415 -209.0234) 
(list 4479.4375 -198.237)))
(apply 'command (append '("pline") coords '("c")))
(setq currobj (ssadd (entlast) currobj))
(setq coords (list 
(list 4479.4375 -198.38) 
(list 4405.415 -209.1664) 
(list 4405.415 -209.3434) 
(list 4479.4375 -198.457)))
(apply 'command (append '("pline") coords '("c")))
(setq currobj (ssadd (entlast) currobj))
(setq coords (list 
(list 4479.4375 -198.6) 
(list 4405.415 -209.4864) 
(list 4405.415 -209.6634) 
(list 4479.4375 -198.677)))
(apply 'command (append '("pline") coords '("c")))
(setq currobj (ssadd (entlast) currobj))
(setq coords (list 
(list 4479.4375 -198.82) 
(list 4405.415 -209.8064) 
(list 4405.415 -209.9834) 
(list 4479.4375 -198.897)))
(apply 'command (append '("pline") coords '("c")))
(setq currobj (ssadd (entlast) currobj))
(setq coords (list 
(list 4479.4375 -199.04) 
(list 4405.415 -210.1264) 
(list 4405.415 -210.3034) 
(list 4479.4375 -199.117)))
(apply 'command (append '("pline") coords '("c")))
(setq currobj (ssadd (entlast) currobj))
(setq coords (list 
(list 4479.4375 -199.26) 
(list 4405.415 -210.4464) 
(list 4405.415 -210.6234) 
(list 4479.4375 -199.337)))
(apply 'command (append '("pline") coords '("c")))
(setq currobj (ssadd (entlast) currobj))
(setq coords (list 
(list 4479.4375 -199.48) 
(list 4405.415 -210.7664) 
(list 4405.415 -210.9434) 
(list 4479.4375 -199.557)))
(apply 'command (append '("pline") coords '("c")))
(setq currobj (ssadd (entlast) currobj))
(setq coords (list 
(list 4479.4375 -199.7) 
(list 4405.415 -211.0864) 
(list 4405.415 -211.2634) 
(list 4479.4375 -199.777)))
(apply 'command (append '("pline") coords '("c")))
(setq currobj (ssadd (entlast) currobj))
(setq coords (list 
(list 4479.4375 -199.92) 
(list 4405.415 -211.4064) 
(list 4405.415 -211.5834) 
(list 4479.4375 -199.997)))
(apply 'command (append '("pline") coords '("c")))
(setq currobj (ssadd (entlast) currobj))
(setq coords (list 
(list 4479.4375 -200.14) 
(list 4405.415 -211.7264) 
(list 4405.415 -211.9034) 
(list 4479.4375 -200.217)))
(apply 'command (append '("pline") coords '("c")))
(setq currobj (ssadd (entlast) currobj))
(setq coords (list 
(list 4479.4375 -200.36) 
(list 4405.415 -212.0464) 
(list 4405.415 -212.2234) 
(list 4479.4375 -200.437)))
(apply 'command (append '("pline") coords '("c")))
(setq currobj (ssadd (entlast) currobj))
(setq coords (list 
(list 4479.4375 -200.58) 
(list 4405.415 -212.3664) 
(list 4405.415 -212.5434) 
(list 4479.4375 -200.657)))
(apply 'command (append '("pline") coords '("c")))
(setq currobj (ssadd (entlast) currobj))
(command "_layer" "set" "nitride" "")
(command "_layer" "set" "text" "")
(command "_circle" "4478.985,-211.8" "0.075")
(command "_circle" "4478.985,-211.5" "0.075")
(command "_circle" "4478.985,-211.2" "0.075")
(command "_circle" "4478.985,-210.9" "0.075")
(command "_circle" "4478.985,-210.6" "0.075")
(command "_circle" "4478.685,-211.8" "0.075")
(command "_circle" "4478.685,-211.5" "0.075")
(command "_circle" "4478.685,-211.2" "0.075")
(command "_circle" "4478.685,-210.9" "0.075")
(command "_circle" "4478.685,-210.6" "0.075")
(command "_circle" "4478.385,-211.8" "0.075")
(command "_circle" "4478.385,-211.5" "0.075")
(command "_circle" "4478.385,-211.2" "0.075")
(command "_circle" "4478.385,-210.9" "0.075")
(command "_circle" "4478.385,-210.6" "0.075")
(command "_circle" "4478.085,-211.8" "0.075")
(command "_circle" "4478.085,-211.5" "0.075")
(command "_circle" "4478.085,-211.2" "0.075")
(command "_circle" "4478.085,-210.9" "0.075")
(command "_circle" "4478.085,-210.6" "0.075")
(command "_circle" "4477.785,-211.8" "0.075")
(command "_circle" "4477.785,-211.5" "0.075")
(command "_circle" "4477.785,-211.2" "0.075")
(command "_circle" "4477.785,-210.9" "0.075")
(command "_circle" "4477.785,-210.6" "0.075")
(command "_layer" "set" "nitride" "")
(setq anglednodearray14 currobj)
(setq currobj nil)
(setq currobj (ssadd))
; DRAWING COOLED SINGLE NANOBEAM
(setq coords (list 
(list 4480.2625 -186.357) 
(list 4480.2625 -181.357) 
(list 4479.7375 -181.357) 
(list 4479.7375 -186.357)))
(apply 'command (append '("pline") coords '("c")))
(setq currobj (ssadd (entlast) currobj))
(command "_layer" "set" "prebias" "")
(command "_rectangle" "4479.7375,-186.357" "4480.2625,-181.357")
(setq currobj (ssadd (entlast) currobj))
(command "_layer" "set" "nitride" "")
(setq coords (list 
(list 4480.2625 -181.357) 
(list 4480.5625 -171.357) 
(list 4480.5625 -171.357) 
(list 4480.5625 -170.357) 
(list 4554.585 -171.107) 
(list 4554.585 -166.164) 
(list 4480.5625 -166.914) 
(list 4480.5625 -165.914) 
(list 4480.5625 -165.914) 
(list 4480.2625 -155.914) 
(list 4479.7375 -155.914) 
(list 4479.4375 -165.914) 
(list 4479.4375 -165.914) 
(list 4479.4375 -166.914) 
(list 4405.415 -166.164) 
(list 4405.415 -171.107) 
(list 4479.4375 -170.357) 
(list 4479.4375 -171.357) 
(list 4479.4375 -171.357) 
(list 4479.7375 -181.357)))
(apply 'command (append '("pline") coords '("c")))
(setq currobj (ssadd (entlast) currobj))
(command "_layer" "set" "prebias" "")
(setq coords (list 
(list 4479.4375 -181.357) 
(list 4479.4375 -170.357) 
(list 4405.415 -171.107) 
(list 4405.415 -166.164) 
(list 4479.4375 -166.914) 
(list 4479.4375 -155.914) 
(list 4480.5625 -155.914) 
(list 4480.5625 -166.914) 
(list 4554.585 -166.164) 
(list 4554.585 -171.107) 
(list 4480.5625 -170.357) 
(list 4480.5625 -181.357)))
(apply 'command (append '("pline") coords '("c")))
(setq currobj (ssadd (entlast) currobj))
(command "_layer" "set" "nitride" "")
(command "_layer" "set" "fda1" "")
(setq coords (list 
(list 4480.5625 -170.214) 
(list 4554.585 -170.964) 
(list 4554.585 -170.787) 
(list 4480.5625 -170.137)))
(apply 'command (append '("pline") coords '("c")))
(setq currobj (ssadd (entlast) currobj))
(setq coords (list 
(list 4480.5625 -169.994) 
(list 4554.585 -170.644) 
(list 4554.585 -170.467) 
(list 4480.5625 -169.917)))
(apply 'command (append '("pline") coords '("c")))
(setq currobj (ssadd (entlast) currobj))
(setq coords (list 
(list 4480.5625 -169.774) 
(list 4554.585 -170.324) 
(list 4554.585 -170.147) 
(list 4480.5625 -169.697)))
(apply 'command (append '("pline") coords '("c")))
(setq currobj (ssadd (entlast) currobj))
(setq coords (list 
(list 4480.5625 -169.554) 
(list 4554.585 -170.004) 
(list 4554.585 -169.827) 
(list 4480.5625 -169.477)))
(apply 'command (append '("pline") coords '("c")))
(setq currobj (ssadd (entlast) currobj))
(setq coords (list 
(list 4480.5625 -169.334) 
(list 4554.585 -169.684) 
(list 4554.585 -169.507) 
(list 4480.5625 -169.257)))
(apply 'command (append '("pline") coords '("c")))
(setq currobj (ssadd (entlast) currobj))
(setq coords (list 
(list 4480.5625 -169.114) 
(list 4554.585 -169.364) 
(list 4554.585 -169.187) 
(list 4480.5625 -169.037)))
(apply 'command (append '("pline") coords '("c")))
(setq currobj (ssadd (entlast) currobj))
(setq coords (list 
(list 4480.5625 -168.894) 
(list 4554.585 -169.044) 
(list 4554.585 -168.867) 
(list 4480.5625 -168.817)))
(apply 'command (append '("pline") coords '("c")))
(setq currobj (ssadd (entlast) currobj))
(setq coords (list 
(list 4480.5625 -168.674) 
(list 4554.585 -168.724) 
(list 4554.585 -168.547) 
(list 4480.5625 -168.597)))
(apply 'command (append '("pline") coords '("c")))
(setq currobj (ssadd (entlast) currobj))
(setq coords (list 
(list 4480.5625 -168.454) 
(list 4554.585 -168.404) 
(list 4554.585 -168.227) 
(list 4480.5625 -168.377)))
(apply 'command (append '("pline") coords '("c")))
(setq currobj (ssadd (entlast) currobj))
(setq coords (list 
(list 4480.5625 -168.234) 
(list 4554.585 -168.084) 
(list 4554.585 -167.907) 
(list 4480.5625 -168.157)))
(apply 'command (append '("pline") coords '("c")))
(setq currobj (ssadd (entlast) currobj))
(setq coords (list 
(list 4480.5625 -168.014) 
(list 4554.585 -167.764) 
(list 4554.585 -167.587) 
(list 4480.5625 -167.937)))
(apply 'command (append '("pline") coords '("c")))
(setq currobj (ssadd (entlast) currobj))
(setq coords (list 
(list 4480.5625 -167.794) 
(list 4554.585 -167.444) 
(list 4554.585 -167.267) 
(list 4480.5625 -167.717)))
(apply 'command (append '("pline") coords '("c")))
(setq currobj (ssadd (entlast) currobj))
(setq coords (list 
(list 4480.5625 -167.574) 
(list 4554.585 -167.124) 
(list 4554.585 -166.947) 
(list 4480.5625 -167.497)))
(apply 'command (append '("pline") coords '("c")))
(setq currobj (ssadd (entlast) currobj))
(setq coords (list 
(list 4480.5625 -167.354) 
(list 4554.585 -166.804) 
(list 4554.585 -166.627) 
(list 4480.5625 -167.277)))
(apply 'command (append '("pline") coords '("c")))
(setq currobj (ssadd (entlast) currobj))
(setq coords (list 
(list 4480.5625 -167.134) 
(list 4554.585 -166.484) 
(list 4554.585 -166.307) 
(list 4480.5625 -167.057)))
(apply 'command (append '("pline") coords '("c")))
(setq currobj (ssadd (entlast) currobj))
(setq coords (list 
(list 4479.4375 -167.057) 
(list 4405.415 -166.307) 
(list 4405.415 -166.484) 
(list 4479.4375 -167.134)))
(apply 'command (append '("pline") coords '("c")))
(setq currobj (ssadd (entlast) currobj))
(setq coords (list 
(list 4479.4375 -167.277) 
(list 4405.415 -166.627) 
(list 4405.415 -166.804) 
(list 4479.4375 -167.354)))
(apply 'command (append '("pline") coords '("c")))
(setq currobj (ssadd (entlast) currobj))
(setq coords (list 
(list 4479.4375 -167.497) 
(list 4405.415 -166.947) 
(list 4405.415 -167.124) 
(list 4479.4375 -167.574)))
(apply 'command (append '("pline") coords '("c")))
(setq currobj (ssadd (entlast) currobj))
(setq coords (list 
(list 4479.4375 -167.717) 
(list 4405.415 -167.267) 
(list 4405.415 -167.444) 
(list 4479.4375 -167.794)))
(apply 'command (append '("pline") coords '("c")))
(setq currobj (ssadd (entlast) currobj))
(setq coords (list 
(list 4479.4375 -167.937) 
(list 4405.415 -167.587) 
(list 4405.415 -167.764) 
(list 4479.4375 -168.014)))
(apply 'command (append '("pline") coords '("c")))
(setq currobj (ssadd (entlast) currobj))
(setq coords (list 
(list 4479.4375 -168.157) 
(list 4405.415 -167.907) 
(list 4405.415 -168.084) 
(list 4479.4375 -168.234)))
(apply 'command (append '("pline") coords '("c")))
(setq currobj (ssadd (entlast) currobj))
(setq coords (list 
(list 4479.4375 -168.377) 
(list 4405.415 -168.227) 
(list 4405.415 -168.404) 
(list 4479.4375 -168.454)))
(apply 'command (append '("pline") coords '("c")))
(setq currobj (ssadd (entlast) currobj))
(setq coords (list 
(list 4479.4375 -168.597) 
(list 4405.415 -168.547) 
(list 4405.415 -168.724) 
(list 4479.4375 -168.674)))
(apply 'command (append '("pline") coords '("c")))
(setq currobj (ssadd (entlast) currobj))
(setq coords (list 
(list 4479.4375 -168.817) 
(list 4405.415 -168.867) 
(list 4405.415 -169.044) 
(list 4479.4375 -168.894)))
(apply 'command (append '("pline") coords '("c")))
(setq currobj (ssadd (entlast) currobj))
(setq coords (list 
(list 4479.4375 -169.037) 
(list 4405.415 -169.187) 
(list 4405.415 -169.364) 
(list 4479.4375 -169.114)))
(apply 'command (append '("pline") coords '("c")))
(setq currobj (ssadd (entlast) currobj))
(setq coords (list 
(list 4479.4375 -169.257) 
(list 4405.415 -169.507) 
(list 4405.415 -169.684) 
(list 4479.4375 -169.334)))
(apply 'command (append '("pline") coords '("c")))
(setq currobj (ssadd (entlast) currobj))
(setq coords (list 
(list 4479.4375 -169.477) 
(list 4405.415 -169.827) 
(list 4405.415 -170.004) 
(list 4479.4375 -169.554)))
(apply 'command (append '("pline") coords '("c")))
(setq currobj (ssadd (entlast) currobj))
(setq coords (list 
(list 4479.4375 -169.697) 
(list 4405.415 -170.147) 
(list 4405.415 -170.324) 
(list 4479.4375 -169.774)))
(apply 'command (append '("pline") coords '("c")))
(setq currobj (ssadd (entlast) currobj))
(setq coords (list 
(list 4479.4375 -169.917) 
(list 4405.415 -170.467) 
(list 4405.415 -170.644) 
(list 4479.4375 -169.994)))
(apply 'command (append '("pline") coords '("c")))
(setq currobj (ssadd (entlast) currobj))
(setq coords (list 
(list 4479.4375 -170.137) 
(list 4405.415 -170.787) 
(list 4405.415 -170.964) 
(list 4479.4375 -170.214)))
(apply 'command (append '("pline") coords '("c")))
(setq currobj (ssadd (entlast) currobj))
(command "_layer" "set" "nitride" "")
(command "_layer" "set" "text" "")
(command "_circle" "4479.0625,-181.357" "0.075")
(command "_circle" "4479.0625,-181.057" "0.075")
(command "_circle" "4479.0625,-180.757" "0.075")
(command "_circle" "4479.0625,-180.457" "0.075")
(command "_circle" "4479.0625,-180.157" "0.075")
(command "_circle" "4478.7625,-181.357" "0.075")
(command "_circle" "4478.7625,-181.057" "0.075")
(command "_circle" "4478.7625,-180.757" "0.075")
(command "_circle" "4478.7625,-180.457" "0.075")
(command "_circle" "4478.7625,-180.157" "0.075")
(command "_circle" "4478.4625,-181.357" "0.075")
(command "_circle" "4478.4625,-181.057" "0.075")
(command "_circle" "4478.4625,-180.757" "0.075")
(command "_circle" "4478.4625,-180.457" "0.075")
(command "_circle" "4478.4625,-180.157" "0.075")
(command "_circle" "4478.1625,-181.357" "0.075")
(command "_circle" "4478.1625,-181.057" "0.075")
(command "_circle" "4478.1625,-180.757" "0.075")
(command "_circle" "4478.1625,-180.457" "0.075")
(command "_circle" "4478.1625,-180.157" "0.075")
(command "_circle" "4477.8625,-181.357" "0.075")
(command "_circle" "4477.8625,-181.057" "0.075")
(command "_circle" "4477.8625,-180.757" "0.075")
(command "_circle" "4477.8625,-180.457" "0.075")
(command "_circle" "4477.8625,-180.157" "0.075")
(command "_layer" "set" "nitride" "")
(setq coords (list 
(list 4480.2625 -155.914) 
(list 4480.2625 -40.2693) 
(list 4479.7375 -40.2693) 
(list 4479.7375 -155.914)))
(apply 'command (append '("pline") coords '("c")))
(setq currobj (ssadd (entlast) currobj))
(command "_layer" "set" "prebias" "")
(command "_rectangle" "4479.7375,-155.914" "4480.2625,-40.2693")
(setq currobj (ssadd (entlast) currobj))
(command "_layer" "set" "nitride" "")
(setq coords (list 
(list 4480.2625 -40.2693) 
(list 4480.5625 -30.2693) 
(list 4480.5625 -30.2693) 
(list 4480.5625 -29.2693) 
(list 4554.585 -30.0193) 
(list 4554.585 -25.0763) 
(list 4480.5625 -25.8263) 
(list 4480.5625 -24.8263) 
(list 4480.5625 -24.8263) 
(list 4480.2625 -14.8263) 
(list 4479.7375 -14.8263) 
(list 4479.4375 -24.8263) 
(list 4479.4375 -24.8263) 
(list 4479.4375 -25.8263) 
(list 4405.415 -25.0763) 
(list 4405.415 -30.0193) 
(list 4479.4375 -29.2693) 
(list 4479.4375 -30.2693) 
(list 4479.4375 -30.2693) 
(list 4479.7375 -40.2693)))
(apply 'command (append '("pline") coords '("c")))
(setq currobj (ssadd (entlast) currobj))
(command "_layer" "set" "prebias" "")
(setq coords (list 
(list 4479.4375 -40.2693) 
(list 4479.4375 -29.2693) 
(list 4405.415 -30.0193) 
(list 4405.415 -25.0763) 
(list 4479.4375 -25.8263) 
(list 4479.4375 -14.8263) 
(list 4480.5625 -14.8263) 
(list 4480.5625 -25.8263) 
(list 4554.585 -25.0763) 
(list 4554.585 -30.0193) 
(list 4480.5625 -29.2693) 
(list 4480.5625 -40.2693)))
(apply 'command (append '("pline") coords '("c")))
(setq currobj (ssadd (entlast) currobj))
(command "_layer" "set" "nitride" "")
(command "_layer" "set" "fda1" "")
(setq coords (list 
(list 4480.5625 -29.1263) 
(list 4554.585 -29.8763) 
(list 4554.585 -29.6993) 
(list 4480.5625 -29.0493)))
(apply 'command (append '("pline") coords '("c")))
(setq currobj (ssadd (entlast) currobj))
(setq coords (list 
(list 4480.5625 -28.9063) 
(list 4554.585 -29.5563) 
(list 4554.585 -29.3793) 
(list 4480.5625 -28.8293)))
(apply 'command (append '("pline") coords '("c")))
(setq currobj (ssadd (entlast) currobj))
(setq coords (list 
(list 4480.5625 -28.6863) 
(list 4554.585 -29.2363) 
(list 4554.585 -29.0593) 
(list 4480.5625 -28.6093)))
(apply 'command (append '("pline") coords '("c")))
(setq currobj (ssadd (entlast) currobj))
(setq coords (list 
(list 4480.5625 -28.4663) 
(list 4554.585 -28.9163) 
(list 4554.585 -28.7393) 
(list 4480.5625 -28.3893)))
(apply 'command (append '("pline") coords '("c")))
(setq currobj (ssadd (entlast) currobj))
(setq coords (list 
(list 4480.5625 -28.2463) 
(list 4554.585 -28.5963) 
(list 4554.585 -28.4193) 
(list 4480.5625 -28.1693)))
(apply 'command (append '("pline") coords '("c")))
(setq currobj (ssadd (entlast) currobj))
(setq coords (list 
(list 4480.5625 -28.0263) 
(list 4554.585 -28.2763) 
(list 4554.585 -28.0993) 
(list 4480.5625 -27.9493)))
(apply 'command (append '("pline") coords '("c")))
(setq currobj (ssadd (entlast) currobj))
(setq coords (list 
(list 4480.5625 -27.8063) 
(list 4554.585 -27.9563) 
(list 4554.585 -27.7793) 
(list 4480.5625 -27.7293)))
(apply 'command (append '("pline") coords '("c")))
(setq currobj (ssadd (entlast) currobj))
(setq coords (list 
(list 4480.5625 -27.5863) 
(list 4554.585 -27.6363) 
(list 4554.585 -27.4593) 
(list 4480.5625 -27.5093)))
(apply 'command (append '("pline") coords '("c")))
(setq currobj (ssadd (entlast) currobj))
(setq coords (list 
(list 4480.5625 -27.3663) 
(list 4554.585 -27.3163) 
(list 4554.585 -27.1393) 
(list 4480.5625 -27.2893)))
(apply 'command (append '("pline") coords '("c")))
(setq currobj (ssadd (entlast) currobj))
(setq coords (list 
(list 4480.5625 -27.1463) 
(list 4554.585 -26.9963) 
(list 4554.585 -26.8193) 
(list 4480.5625 -27.0693)))
(apply 'command (append '("pline") coords '("c")))
(setq currobj (ssadd (entlast) currobj))
(setq coords (list 
(list 4480.5625 -26.9263) 
(list 4554.585 -26.6763) 
(list 4554.585 -26.4993) 
(list 4480.5625 -26.8493)))
(apply 'command (append '("pline") coords '("c")))
(setq currobj (ssadd (entlast) currobj))
(setq coords (list 
(list 4480.5625 -26.7063) 
(list 4554.585 -26.3563) 
(list 4554.585 -26.1793) 
(list 4480.5625 -26.6293)))
(apply 'command (append '("pline") coords '("c")))
(setq currobj (ssadd (entlast) currobj))
(setq coords (list 
(list 4480.5625 -26.4863) 
(list 4554.585 -26.0363) 
(list 4554.585 -25.8593) 
(list 4480.5625 -26.4093)))
(apply 'command (append '("pline") coords '("c")))
(setq currobj (ssadd (entlast) currobj))
(setq coords (list 
(list 4480.5625 -26.2663) 
(list 4554.585 -25.7163) 
(list 4554.585 -25.5393) 
(list 4480.5625 -26.1893)))
(apply 'command (append '("pline") coords '("c")))
(setq currobj (ssadd (entlast) currobj))
(setq coords (list 
(list 4480.5625 -26.0463) 
(list 4554.585 -25.3963) 
(list 4554.585 -25.2193) 
(list 4480.5625 -25.9693)))
(apply 'command (append '("pline") coords '("c")))
(setq currobj (ssadd (entlast) currobj))
(setq coords (list 
(list 4479.4375 -25.9693) 
(list 4405.415 -25.2193) 
(list 4405.415 -25.3963) 
(list 4479.4375 -26.0463)))
(apply 'command (append '("pline") coords '("c")))
(setq currobj (ssadd (entlast) currobj))
(setq coords (list 
(list 4479.4375 -26.1893) 
(list 4405.415 -25.5393) 
(list 4405.415 -25.7163) 
(list 4479.4375 -26.2663)))
(apply 'command (append '("pline") coords '("c")))
(setq currobj (ssadd (entlast) currobj))
(setq coords (list 
(list 4479.4375 -26.4093) 
(list 4405.415 -25.8593) 
(list 4405.415 -26.0363) 
(list 4479.4375 -26.4863)))
(apply 'command (append '("pline") coords '("c")))
(setq currobj (ssadd (entlast) currobj))
(setq coords (list 
(list 4479.4375 -26.6293) 
(list 4405.415 -26.1793) 
(list 4405.415 -26.3563) 
(list 4479.4375 -26.7063)))
(apply 'command (append '("pline") coords '("c")))
(setq currobj (ssadd (entlast) currobj))
(setq coords (list 
(list 4479.4375 -26.8493) 
(list 4405.415 -26.4993) 
(list 4405.415 -26.6763) 
(list 4479.4375 -26.9263)))
(apply 'command (append '("pline") coords '("c")))
(setq currobj (ssadd (entlast) currobj))
(setq coords (list 
(list 4479.4375 -27.0693) 
(list 4405.415 -26.8193) 
(list 4405.415 -26.9963) 
(list 4479.4375 -27.1463)))
(apply 'command (append '("pline") coords '("c")))
(setq currobj (ssadd (entlast) currobj))
(setq coords (list 
(list 4479.4375 -27.2893) 
(list 4405.415 -27.1393) 
(list 4405.415 -27.3163) 
(list 4479.4375 -27.3663)))
(apply 'command (append '("pline") coords '("c")))
(setq currobj (ssadd (entlast) currobj))
(setq coords (list 
(list 4479.4375 -27.5093) 
(list 4405.415 -27.4593) 
(list 4405.415 -27.6363) 
(list 4479.4375 -27.5863)))
(apply 'command (append '("pline") coords '("c")))
(setq currobj (ssadd (entlast) currobj))
(setq coords (list 
(list 4479.4375 -27.7293) 
(list 4405.415 -27.7793) 
(list 4405.415 -27.9563) 
(list 4479.4375 -27.8063)))
(apply 'command (append '("pline") coords '("c")))
(setq currobj (ssadd (entlast) currobj))
(setq coords (list 
(list 4479.4375 -27.9493) 
(list 4405.415 -28.0993) 
(list 4405.415 -28.2763) 
(list 4479.4375 -28.0263)))
(apply 'command (append '("pline") coords '("c")))
(setq currobj (ssadd (entlast) currobj))
(setq coords (list 
(list 4479.4375 -28.1693) 
(list 4405.415 -28.4193) 
(list 4405.415 -28.5963) 
(list 4479.4375 -28.2463)))
(apply 'command (append '("pline") coords '("c")))
(setq currobj (ssadd (entlast) currobj))
(setq coords (list 
(list 4479.4375 -28.3893) 
(list 4405.415 -28.7393) 
(list 4405.415 -28.9163) 
(list 4479.4375 -28.4663)))
(apply 'command (append '("pline") coords '("c")))
(setq currobj (ssadd (entlast) currobj))
(setq coords (list 
(list 4479.4375 -28.6093) 
(list 4405.415 -29.0593) 
(list 4405.415 -29.2363) 
(list 4479.4375 -28.6863)))
(apply 'command (append '("pline") coords '("c")))
(setq currobj (ssadd (entlast) currobj))
(setq coords (list 
(list 4479.4375 -28.8293) 
(list 4405.415 -29.3793) 
(list 4405.415 -29.5563) 
(list 4479.4375 -28.9063)))
(apply 'command (append '("pline") coords '("c")))
(setq currobj (ssadd (entlast) currobj))
(setq coords (list 
(list 4479.4375 -29.0493) 
(list 4405.415 -29.6993) 
(list 4405.415 -29.8763) 
(list 4479.4375 -29.1263)))
(apply 'command (append '("pline") coords '("c")))
(setq currobj (ssadd (entlast) currobj))
(command "_layer" "set" "nitride" "")
(command "_layer" "set" "text" "")
(command "_circle" "4479.0625,-40.2693" "0.075")
(command "_circle" "4479.0625,-39.9693" "0.075")
(command "_circle" "4479.0625,-39.6693" "0.075")
(command "_circle" "4479.0625,-39.3693" "0.075")
(command "_circle" "4479.0625,-39.0693" "0.075")
(command "_circle" "4478.7625,-40.2693" "0.075")
(command "_circle" "4478.7625,-39.9693" "0.075")
(command "_circle" "4478.7625,-39.6693" "0.075")
(command "_circle" "4478.7625,-39.3693" "0.075")
(command "_circle" "4478.7625,-39.0693" "0.075")
(command "_circle" "4478.4625,-40.2693" "0.075")
(command "_circle" "4478.4625,-39.9693" "0.075")
(command "_circle" "4478.4625,-39.6693" "0.075")
(command "_circle" "4478.4625,-39.3693" "0.075")
(command "_circle" "4478.4625,-39.0693" "0.075")
(command "_circle" "4478.1625,-40.2693" "0.075")
(command "_circle" "4478.1625,-39.9693" "0.075")
(command "_circle" "4478.1625,-39.6693" "0.075")
(command "_circle" "4478.1625,-39.3693" "0.075")
(command "_circle" "4478.1625,-39.0693" "0.075")
(command "_circle" "4477.8625,-40.2693" "0.075")
(command "_circle" "4477.8625,-39.9693" "0.075")
(command "_circle" "4477.8625,-39.6693" "0.075")
(command "_circle" "4477.8625,-39.3693" "0.075")
(command "_circle" "4477.8625,-39.0693" "0.075")
(command "_layer" "set" "nitride" "")
(setq coords (list 
(list 4480.2625 -14.8263) 
(list 4480.2625 100.8184) 
(list 4479.7375 100.8184) 
(list 4479.7375 -14.8263)))
(apply 'command (append '("pline") coords '("c")))
(setq currobj (ssadd (entlast) currobj))
(command "_layer" "set" "prebias" "")
(command "_rectangle" "4479.7375,-14.8263" "4480.2625,100.8184")
(setq currobj (ssadd (entlast) currobj))
(command "_layer" "set" "nitride" "")
(setq coords (list 
(list 4480.2625 100.8184) 
(list 4480.5625 110.8184) 
(list 4480.5625 110.8184) 
(list 4480.5625 111.8184) 
(list 4554.585 111.0684) 
(list 4554.585 116.0114) 
(list 4480.5625 115.2614) 
(list 4480.5625 116.2614) 
(list 4480.5625 116.2614) 
(list 4480.2625 126.2614) 
(list 4479.7375 126.2614) 
(list 4479.4375 116.2614) 
(list 4479.4375 116.2614) 
(list 4479.4375 115.2614) 
(list 4405.415 116.0114) 
(list 4405.415 111.0684) 
(list 4479.4375 111.8184) 
(list 4479.4375 110.8184) 
(list 4479.4375 110.8184) 
(list 4479.7375 100.8184)))
(apply 'command (append '("pline") coords '("c")))
(setq currobj (ssadd (entlast) currobj))
(command "_layer" "set" "prebias" "")
(setq coords (list 
(list 4479.4375 100.8184) 
(list 4479.4375 111.8184) 
(list 4405.415 111.0684) 
(list 4405.415 116.0114) 
(list 4479.4375 115.2614) 
(list 4479.4375 126.2614) 
(list 4480.5625 126.2614) 
(list 4480.5625 115.2614) 
(list 4554.585 116.0114) 
(list 4554.585 111.0684) 
(list 4480.5625 111.8184) 
(list 4480.5625 100.8184)))
(apply 'command (append '("pline") coords '("c")))
(setq currobj (ssadd (entlast) currobj))
(command "_layer" "set" "nitride" "")
(command "_layer" "set" "fda1" "")
(setq coords (list 
(list 4480.5625 111.9614) 
(list 4554.585 111.2114) 
(list 4554.585 111.3884) 
(list 4480.5625 112.0384)))
(apply 'command (append '("pline") coords '("c")))
(setq currobj (ssadd (entlast) currobj))
(setq coords (list 
(list 4480.5625 112.1814) 
(list 4554.585 111.5314) 
(list 4554.585 111.7084) 
(list 4480.5625 112.2584)))
(apply 'command (append '("pline") coords '("c")))
(setq currobj (ssadd (entlast) currobj))
(setq coords (list 
(list 4480.5625 112.4014) 
(list 4554.585 111.8514) 
(list 4554.585 112.0284) 
(list 4480.5625 112.4784)))
(apply 'command (append '("pline") coords '("c")))
(setq currobj (ssadd (entlast) currobj))
(setq coords (list 
(list 4480.5625 112.6214) 
(list 4554.585 112.1714) 
(list 4554.585 112.3484) 
(list 4480.5625 112.6984)))
(apply 'command (append '("pline") coords '("c")))
(setq currobj (ssadd (entlast) currobj))
(setq coords (list 
(list 4480.5625 112.8414) 
(list 4554.585 112.4914) 
(list 4554.585 112.6684) 
(list 4480.5625 112.9184)))
(apply 'command (append '("pline") coords '("c")))
(setq currobj (ssadd (entlast) currobj))
(setq coords (list 
(list 4480.5625 113.0614) 
(list 4554.585 112.8114) 
(list 4554.585 112.9884) 
(list 4480.5625 113.1384)))
(apply 'command (append '("pline") coords '("c")))
(setq currobj (ssadd (entlast) currobj))
(setq coords (list 
(list 4480.5625 113.2814) 
(list 4554.585 113.1314) 
(list 4554.585 113.3084) 
(list 4480.5625 113.3584)))
(apply 'command (append '("pline") coords '("c")))
(setq currobj (ssadd (entlast) currobj))
(setq coords (list 
(list 4480.5625 113.5014) 
(list 4554.585 113.4514) 
(list 4554.585 113.6284) 
(list 4480.5625 113.5784)))
(apply 'command (append '("pline") coords '("c")))
(setq currobj (ssadd (entlast) currobj))
(setq coords (list 
(list 4480.5625 113.7214) 
(list 4554.585 113.7714) 
(list 4554.585 113.9484) 
(list 4480.5625 113.7984)))
(apply 'command (append '("pline") coords '("c")))
(setq currobj (ssadd (entlast) currobj))
(setq coords (list 
(list 4480.5625 113.9414) 
(list 4554.585 114.0914) 
(list 4554.585 114.2684) 
(list 4480.5625 114.0184)))
(apply 'command (append '("pline") coords '("c")))
(setq currobj (ssadd (entlast) currobj))
(setq coords (list 
(list 4480.5625 114.1614) 
(list 4554.585 114.4114) 
(list 4554.585 114.5884) 
(list 4480.5625 114.2384)))
(apply 'command (append '("pline") coords '("c")))
(setq currobj (ssadd (entlast) currobj))
(setq coords (list 
(list 4480.5625 114.3814) 
(list 4554.585 114.7314) 
(list 4554.585 114.9084) 
(list 4480.5625 114.4584)))
(apply 'command (append '("pline") coords '("c")))
(setq currobj (ssadd (entlast) currobj))
(setq coords (list 
(list 4480.5625 114.6014) 
(list 4554.585 115.0514) 
(list 4554.585 115.2284) 
(list 4480.5625 114.6784)))
(apply 'command (append '("pline") coords '("c")))
(setq currobj (ssadd (entlast) currobj))
(setq coords (list 
(list 4480.5625 114.8214) 
(list 4554.585 115.3714) 
(list 4554.585 115.5484) 
(list 4480.5625 114.8984)))
(apply 'command (append '("pline") coords '("c")))
(setq currobj (ssadd (entlast) currobj))
(setq coords (list 
(list 4480.5625 115.0414) 
(list 4554.585 115.6914) 
(list 4554.585 115.8684) 
(list 4480.5625 115.1184)))
(apply 'command (append '("pline") coords '("c")))
(setq currobj (ssadd (entlast) currobj))
(setq coords (list 
(list 4479.4375 115.1184) 
(list 4405.415 115.8684) 
(list 4405.415 115.6914) 
(list 4479.4375 115.0414)))
(apply 'command (append '("pline") coords '("c")))
(setq currobj (ssadd (entlast) currobj))
(setq coords (list 
(list 4479.4375 114.8984) 
(list 4405.415 115.5484) 
(list 4405.415 115.3714) 
(list 4479.4375 114.8214)))
(apply 'command (append '("pline") coords '("c")))
(setq currobj (ssadd (entlast) currobj))
(setq coords (list 
(list 4479.4375 114.6784) 
(list 4405.415 115.2284) 
(list 4405.415 115.0514) 
(list 4479.4375 114.6014)))
(apply 'command (append '("pline") coords '("c")))
(setq currobj (ssadd (entlast) currobj))
(setq coords (list 
(list 4479.4375 114.4584) 
(list 4405.415 114.9084) 
(list 4405.415 114.7314) 
(list 4479.4375 114.3814)))
(apply 'command (append '("pline") coords '("c")))
(setq currobj (ssadd (entlast) currobj))
(setq coords (list 
(list 4479.4375 114.2384) 
(list 4405.415 114.5884) 
(list 4405.415 114.4114) 
(list 4479.4375 114.1614)))
(apply 'command (append '("pline") coords '("c")))
(setq currobj (ssadd (entlast) currobj))
(setq coords (list 
(list 4479.4375 114.0184) 
(list 4405.415 114.2684) 
(list 4405.415 114.0914) 
(list 4479.4375 113.9414)))
(apply 'command (append '("pline") coords '("c")))
(setq currobj (ssadd (entlast) currobj))
(setq coords (list 
(list 4479.4375 113.7984) 
(list 4405.415 113.9484) 
(list 4405.415 113.7714) 
(list 4479.4375 113.7214)))
(apply 'command (append '("pline") coords '("c")))
(setq currobj (ssadd (entlast) currobj))
(setq coords (list 
(list 4479.4375 113.5784) 
(list 4405.415 113.6284) 
(list 4405.415 113.4514) 
(list 4479.4375 113.5014)))
(apply 'command (append '("pline") coords '("c")))
(setq currobj (ssadd (entlast) currobj))
(setq coords (list 
(list 4479.4375 113.3584) 
(list 4405.415 113.3084) 
(list 4405.415 113.1314) 
(list 4479.4375 113.2814)))
(apply 'command (append '("pline") coords '("c")))
(setq currobj (ssadd (entlast) currobj))
(setq coords (list 
(list 4479.4375 113.1384) 
(list 4405.415 112.9884) 
(list 4405.415 112.8114) 
(list 4479.4375 113.0614)))
(apply 'command (append '("pline") coords '("c")))
(setq currobj (ssadd (entlast) currobj))
(setq coords (list 
(list 4479.4375 112.9184) 
(list 4405.415 112.6684) 
(list 4405.415 112.4914) 
(list 4479.4375 112.8414)))
(apply 'command (append '("pline") coords '("c")))
(setq currobj (ssadd (entlast) currobj))
(setq coords (list 
(list 4479.4375 112.6984) 
(list 4405.415 112.3484) 
(list 4405.415 112.1714) 
(list 4479.4375 112.6214)))
(apply 'command (append '("pline") coords '("c")))
(setq currobj (ssadd (entlast) currobj))
(setq coords (list 
(list 4479.4375 112.4784) 
(list 4405.415 112.0284) 
(list 4405.415 111.8514) 
(list 4479.4375 112.4014)))
(apply 'command (append '("pline") coords '("c")))
(setq currobj (ssadd (entlast) currobj))
(setq coords (list 
(list 4479.4375 112.2584) 
(list 4405.415 111.7084) 
(list 4405.415 111.5314) 
(list 4479.4375 112.1814)))
(apply 'command (append '("pline") coords '("c")))
(setq currobj (ssadd (entlast) currobj))
(setq coords (list 
(list 4479.4375 112.0384) 
(list 4405.415 111.3884) 
(list 4405.415 111.2114) 
(list 4479.4375 111.9614)))
(apply 'command (append '("pline") coords '("c")))
(setq currobj (ssadd (entlast) currobj))
(command "_layer" "set" "nitride" "")
(command "_layer" "set" "text" "")
(command "_circle" "4479.0625,100.8184" "0.075")
(command "_circle" "4479.0625,101.1184" "0.075")
(command "_circle" "4479.0625,101.4184" "0.075")
(command "_circle" "4479.0625,101.7184" "0.075")
(command "_circle" "4479.0625,102.0184" "0.075")
(command "_circle" "4478.7625,100.8184" "0.075")
(command "_circle" "4478.7625,101.1184" "0.075")
(command "_circle" "4478.7625,101.4184" "0.075")
(command "_circle" "4478.7625,101.7184" "0.075")
(command "_circle" "4478.7625,102.0184" "0.075")
(command "_circle" "4478.4625,100.8184" "0.075")
(command "_circle" "4478.4625,101.1184" "0.075")
(command "_circle" "4478.4625,101.4184" "0.075")
(command "_circle" "4478.4625,101.7184" "0.075")
(command "_circle" "4478.4625,102.0184" "0.075")
(command "_circle" "4478.1625,100.8184" "0.075")
(command "_circle" "4478.1625,101.1184" "0.075")
(command "_circle" "4478.1625,101.4184" "0.075")
(command "_circle" "4478.1625,101.7184" "0.075")
(command "_circle" "4478.1625,102.0184" "0.075")
(command "_circle" "4477.8625,100.8184" "0.075")
(command "_circle" "4477.8625,101.1184" "0.075")
(command "_circle" "4477.8625,101.4184" "0.075")
(command "_circle" "4477.8625,101.7184" "0.075")
(command "_circle" "4477.8625,102.0184" "0.075")
(command "_layer" "set" "nitride" "")
(setq coords (list 
(list 4480.2625 126.2614) 
(list 4480.2625 241.9061) 
(list 4479.7375 241.9061) 
(list 4479.7375 126.2614)))
(apply 'command (append '("pline") coords '("c")))
(setq currobj (ssadd (entlast) currobj))
(command "_layer" "set" "prebias" "")
(command "_rectangle" "4479.7375,126.2614" "4480.2625,241.9061")
(setq currobj (ssadd (entlast) currobj))
(command "_layer" "set" "nitride" "")
(setq coords (list 
(list 4480.2625 241.9061) 
(list 4480.5625 251.9061) 
(list 4480.5625 251.9061) 
(list 4480.5625 252.9061) 
(list 4554.585 252.1561) 
(list 4554.585 257.0991) 
(list 4480.5625 256.3491) 
(list 4480.5625 257.3491) 
(list 4480.5625 257.3491) 
(list 4480.2625 267.3491) 
(list 4479.7375 267.3491) 
(list 4479.4375 257.3491) 
(list 4479.4375 257.3491) 
(list 4479.4375 256.3491) 
(list 4405.415 257.0991) 
(list 4405.415 252.1561) 
(list 4479.4375 252.9061) 
(list 4479.4375 251.9061) 
(list 4479.4375 251.9061) 
(list 4479.7375 241.9061)))
(apply 'command (append '("pline") coords '("c")))
(setq currobj (ssadd (entlast) currobj))
(command "_layer" "set" "prebias" "")
(setq coords (list 
(list 4479.4375 241.9061) 
(list 4479.4375 252.9061) 
(list 4405.415 252.1561) 
(list 4405.415 257.0991) 
(list 4479.4375 256.3491) 
(list 4479.4375 267.3491) 
(list 4480.5625 267.3491) 
(list 4480.5625 256.3491) 
(list 4554.585 257.0991) 
(list 4554.585 252.1561) 
(list 4480.5625 252.9061) 
(list 4480.5625 241.9061)))
(apply 'command (append '("pline") coords '("c")))
(setq currobj (ssadd (entlast) currobj))
(command "_layer" "set" "nitride" "")
(command "_layer" "set" "fda1" "")
(setq coords (list 
(list 4480.5625 253.0491) 
(list 4554.585 252.2991) 
(list 4554.585 252.4761) 
(list 4480.5625 253.1261)))
(apply 'command (append '("pline") coords '("c")))
(setq currobj (ssadd (entlast) currobj))
(setq coords (list 
(list 4480.5625 253.2691) 
(list 4554.585 252.6191) 
(list 4554.585 252.7961) 
(list 4480.5625 253.3461)))
(apply 'command (append '("pline") coords '("c")))
(setq currobj (ssadd (entlast) currobj))
(setq coords (list 
(list 4480.5625 253.4891) 
(list 4554.585 252.9391) 
(list 4554.585 253.1161) 
(list 4480.5625 253.5661)))
(apply 'command (append '("pline") coords '("c")))
(setq currobj (ssadd (entlast) currobj))
(setq coords (list 
(list 4480.5625 253.7091) 
(list 4554.585 253.2591) 
(list 4554.585 253.4361) 
(list 4480.5625 253.7861)))
(apply 'command (append '("pline") coords '("c")))
(setq currobj (ssadd (entlast) currobj))
(setq coords (list 
(list 4480.5625 253.9291) 
(list 4554.585 253.5791) 
(list 4554.585 253.7561) 
(list 4480.5625 254.0061)))
(apply 'command (append '("pline") coords '("c")))
(setq currobj (ssadd (entlast) currobj))
(setq coords (list 
(list 4480.5625 254.1491) 
(list 4554.585 253.8991) 
(list 4554.585 254.0761) 
(list 4480.5625 254.2261)))
(apply 'command (append '("pline") coords '("c")))
(setq currobj (ssadd (entlast) currobj))
(setq coords (list 
(list 4480.5625 254.3691) 
(list 4554.585 254.2191) 
(list 4554.585 254.3961) 
(list 4480.5625 254.4461)))
(apply 'command (append '("pline") coords '("c")))
(setq currobj (ssadd (entlast) currobj))
(setq coords (list 
(list 4480.5625 254.5891) 
(list 4554.585 254.5391) 
(list 4554.585 254.7161) 
(list 4480.5625 254.6661)))
(apply 'command (append '("pline") coords '("c")))
(setq currobj (ssadd (entlast) currobj))
(setq coords (list 
(list 4480.5625 254.8091) 
(list 4554.585 254.8591) 
(list 4554.585 255.0361) 
(list 4480.5625 254.8861)))
(apply 'command (append '("pline") coords '("c")))
(setq currobj (ssadd (entlast) currobj))
(setq coords (list 
(list 4480.5625 255.0291) 
(list 4554.585 255.1791) 
(list 4554.585 255.3561) 
(list 4480.5625 255.1061)))
(apply 'command (append '("pline") coords '("c")))
(setq currobj (ssadd (entlast) currobj))
(setq coords (list 
(list 4480.5625 255.2491) 
(list 4554.585 255.4991) 
(list 4554.585 255.6761) 
(list 4480.5625 255.3261)))
(apply 'command (append '("pline") coords '("c")))
(setq currobj (ssadd (entlast) currobj))
(setq coords (list 
(list 4480.5625 255.4691) 
(list 4554.585 255.8191) 
(list 4554.585 255.9961) 
(list 4480.5625 255.5461)))
(apply 'command (append '("pline") coords '("c")))
(setq currobj (ssadd (entlast) currobj))
(setq coords (list 
(list 4480.5625 255.6891) 
(list 4554.585 256.1391) 
(list 4554.585 256.3161) 
(list 4480.5625 255.7661)))
(apply 'command (append '("pline") coords '("c")))
(setq currobj (ssadd (entlast) currobj))
(setq coords (list 
(list 4480.5625 255.9091) 
(list 4554.585 256.4591) 
(list 4554.585 256.6361) 
(list 4480.5625 255.9861)))
(apply 'command (append '("pline") coords '("c")))
(setq currobj (ssadd (entlast) currobj))
(setq coords (list 
(list 4480.5625 256.1291) 
(list 4554.585 256.7791) 
(list 4554.585 256.9561) 
(list 4480.5625 256.2061)))
(apply 'command (append '("pline") coords '("c")))
(setq currobj (ssadd (entlast) currobj))
(setq coords (list 
(list 4479.4375 256.2061) 
(list 4405.415 256.9561) 
(list 4405.415 256.7791) 
(list 4479.4375 256.1291)))
(apply 'command (append '("pline") coords '("c")))
(setq currobj (ssadd (entlast) currobj))
(setq coords (list 
(list 4479.4375 255.9861) 
(list 4405.415 256.6361) 
(list 4405.415 256.4591) 
(list 4479.4375 255.9091)))
(apply 'command (append '("pline") coords '("c")))
(setq currobj (ssadd (entlast) currobj))
(setq coords (list 
(list 4479.4375 255.7661) 
(list 4405.415 256.3161) 
(list 4405.415 256.1391) 
(list 4479.4375 255.6891)))
(apply 'command (append '("pline") coords '("c")))
(setq currobj (ssadd (entlast) currobj))
(setq coords (list 
(list 4479.4375 255.5461) 
(list 4405.415 255.9961) 
(list 4405.415 255.8191) 
(list 4479.4375 255.4691)))
(apply 'command (append '("pline") coords '("c")))
(setq currobj (ssadd (entlast) currobj))
(setq coords (list 
(list 4479.4375 255.3261) 
(list 4405.415 255.6761) 
(list 4405.415 255.4991) 
(list 4479.4375 255.2491)))
(apply 'command (append '("pline") coords '("c")))
(setq currobj (ssadd (entlast) currobj))
(setq coords (list 
(list 4479.4375 255.1061) 
(list 4405.415 255.3561) 
(list 4405.415 255.1791) 
(list 4479.4375 255.0291)))
(apply 'command (append '("pline") coords '("c")))
(setq currobj (ssadd (entlast) currobj))
(setq coords (list 
(list 4479.4375 254.8861) 
(list 4405.415 255.0361) 
(list 4405.415 254.8591) 
(list 4479.4375 254.8091)))
(apply 'command (append '("pline") coords '("c")))
(setq currobj (ssadd (entlast) currobj))
(setq coords (list 
(list 4479.4375 254.6661) 
(list 4405.415 254.7161) 
(list 4405.415 254.5391) 
(list 4479.4375 254.5891)))
(apply 'command (append '("pline") coords '("c")))
(setq currobj (ssadd (entlast) currobj))
(setq coords (list 
(list 4479.4375 254.4461) 
(list 4405.415 254.3961) 
(list 4405.415 254.2191) 
(list 4479.4375 254.3691)))
(apply 'command (append '("pline") coords '("c")))
(setq currobj (ssadd (entlast) currobj))
(setq coords (list 
(list 4479.4375 254.2261) 
(list 4405.415 254.0761) 
(list 4405.415 253.8991) 
(list 4479.4375 254.1491)))
(apply 'command (append '("pline") coords '("c")))
(setq currobj (ssadd (entlast) currobj))
(setq coords (list 
(list 4479.4375 254.0061) 
(list 4405.415 253.7561) 
(list 4405.415 253.5791) 
(list 4479.4375 253.9291)))
(apply 'command (append '("pline") coords '("c")))
(setq currobj (ssadd (entlast) currobj))
(setq coords (list 
(list 4479.4375 253.7861) 
(list 4405.415 253.4361) 
(list 4405.415 253.2591) 
(list 4479.4375 253.7091)))
(apply 'command (append '("pline") coords '("c")))
(setq currobj (ssadd (entlast) currobj))
(setq coords (list 
(list 4479.4375 253.5661) 
(list 4405.415 253.1161) 
(list 4405.415 252.9391) 
(list 4479.4375 253.4891)))
(apply 'command (append '("pline") coords '("c")))
(setq currobj (ssadd (entlast) currobj))
(setq coords (list 
(list 4479.4375 253.3461) 
(list 4405.415 252.7961) 
(list 4405.415 252.6191) 
(list 4479.4375 253.2691)))
(apply 'command (append '("pline") coords '("c")))
(setq currobj (ssadd (entlast) currobj))
(setq coords (list 
(list 4479.4375 253.1261) 
(list 4405.415 252.4761) 
(list 4405.415 252.2991) 
(list 4479.4375 253.0491)))
(apply 'command (append '("pline") coords '("c")))
(setq currobj (ssadd (entlast) currobj))
(command "_layer" "set" "nitride" "")
(command "_layer" "set" "text" "")
(command "_circle" "4479.0625,241.9061" "0.075")
(command "_circle" "4479.0625,242.2061" "0.075")
(command "_circle" "4479.0625,242.5061" "0.075")
(command "_circle" "4479.0625,242.8061" "0.075")
(command "_circle" "4479.0625,243.1061" "0.075")
(command "_circle" "4478.7625,241.9061" "0.075")
(command "_circle" "4478.7625,242.2061" "0.075")
(command "_circle" "4478.7625,242.5061" "0.075")
(command "_circle" "4478.7625,242.8061" "0.075")
(command "_circle" "4478.7625,243.1061" "0.075")
(command "_circle" "4478.4625,241.9061" "0.075")
(command "_circle" "4478.4625,242.2061" "0.075")
(command "_circle" "4478.4625,242.5061" "0.075")
(command "_circle" "4478.4625,242.8061" "0.075")
(command "_circle" "4478.4625,243.1061" "0.075")
(command "_circle" "4478.1625,241.9061" "0.075")
(command "_circle" "4478.1625,242.2061" "0.075")
(command "_circle" "4478.1625,242.5061" "0.075")
(command "_circle" "4478.1625,242.8061" "0.075")
(command "_circle" "4478.1625,243.1061" "0.075")
(command "_circle" "4477.8625,241.9061" "0.075")
(command "_circle" "4477.8625,242.2061" "0.075")
(command "_circle" "4477.8625,242.5061" "0.075")
(command "_circle" "4477.8625,242.8061" "0.075")
(command "_circle" "4477.8625,243.1061" "0.075")
(command "_layer" "set" "nitride" "")
(setq coords (list 
(list 4480.2625 267.3491) 
(list 4480.2625 382.9939) 
(list 4479.7375 382.9939) 
(list 4479.7375 267.3491)))
(apply 'command (append '("pline") coords '("c")))
(setq currobj (ssadd (entlast) currobj))
(command "_layer" "set" "prebias" "")
(command "_rectangle" "4479.7375,267.3491" "4480.2625,382.9939")
(setq currobj (ssadd (entlast) currobj))
(command "_layer" "set" "nitride" "")
(setq coords (list 
(list 4480.2625 382.9939) 
(list 4480.5625 392.9939) 
(list 4480.5625 392.9939) 
(list 4480.5625 393.9939) 
(list 4554.585 393.2439) 
(list 4554.585 398.1869) 
(list 4480.5625 397.4369) 
(list 4480.5625 398.4369) 
(list 4480.5625 398.4369) 
(list 4480.2625 408.4369) 
(list 4479.7375 408.4369) 
(list 4479.4375 398.4369) 
(list 4479.4375 398.4369) 
(list 4479.4375 397.4369) 
(list 4405.415 398.1869) 
(list 4405.415 393.2439) 
(list 4479.4375 393.9939) 
(list 4479.4375 392.9939) 
(list 4479.4375 392.9939) 
(list 4479.7375 382.9939)))
(apply 'command (append '("pline") coords '("c")))
(setq currobj (ssadd (entlast) currobj))
(command "_layer" "set" "prebias" "")
(setq coords (list 
(list 4479.4375 382.9939) 
(list 4479.4375 393.9939) 
(list 4405.415 393.2439) 
(list 4405.415 398.1869) 
(list 4479.4375 397.4369) 
(list 4479.4375 408.4369) 
(list 4480.5625 408.4369) 
(list 4480.5625 397.4369) 
(list 4554.585 398.1869) 
(list 4554.585 393.2439) 
(list 4480.5625 393.9939) 
(list 4480.5625 382.9939)))
(apply 'command (append '("pline") coords '("c")))
(setq currobj (ssadd (entlast) currobj))
(command "_layer" "set" "nitride" "")
(command "_layer" "set" "fda1" "")
(setq coords (list 
(list 4480.5625 394.1369) 
(list 4554.585 393.3869) 
(list 4554.585 393.5639) 
(list 4480.5625 394.2139)))
(apply 'command (append '("pline") coords '("c")))
(setq currobj (ssadd (entlast) currobj))
(setq coords (list 
(list 4480.5625 394.3569) 
(list 4554.585 393.7069) 
(list 4554.585 393.8839) 
(list 4480.5625 394.4339)))
(apply 'command (append '("pline") coords '("c")))
(setq currobj (ssadd (entlast) currobj))
(setq coords (list 
(list 4480.5625 394.5769) 
(list 4554.585 394.0269) 
(list 4554.585 394.2039) 
(list 4480.5625 394.6539)))
(apply 'command (append '("pline") coords '("c")))
(setq currobj (ssadd (entlast) currobj))
(setq coords (list 
(list 4480.5625 394.7969) 
(list 4554.585 394.3469) 
(list 4554.585 394.5239) 
(list 4480.5625 394.8739)))
(apply 'command (append '("pline") coords '("c")))
(setq currobj (ssadd (entlast) currobj))
(setq coords (list 
(list 4480.5625 395.0169) 
(list 4554.585 394.6669) 
(list 4554.585 394.8439) 
(list 4480.5625 395.0939)))
(apply 'command (append '("pline") coords '("c")))
(setq currobj (ssadd (entlast) currobj))
(setq coords (list 
(list 4480.5625 395.2369) 
(list 4554.585 394.9869) 
(list 4554.585 395.1639) 
(list 4480.5625 395.3139)))
(apply 'command (append '("pline") coords '("c")))
(setq currobj (ssadd (entlast) currobj))
(setq coords (list 
(list 4480.5625 395.4569) 
(list 4554.585 395.3069) 
(list 4554.585 395.4839) 
(list 4480.5625 395.5339)))
(apply 'command (append '("pline") coords '("c")))
(setq currobj (ssadd (entlast) currobj))
(setq coords (list 
(list 4480.5625 395.6769) 
(list 4554.585 395.6269) 
(list 4554.585 395.8039) 
(list 4480.5625 395.7539)))
(apply 'command (append '("pline") coords '("c")))
(setq currobj (ssadd (entlast) currobj))
(setq coords (list 
(list 4480.5625 395.8969) 
(list 4554.585 395.9469) 
(list 4554.585 396.1239) 
(list 4480.5625 395.9739)))
(apply 'command (append '("pline") coords '("c")))
(setq currobj (ssadd (entlast) currobj))
(setq coords (list 
(list 4480.5625 396.1169) 
(list 4554.585 396.2669) 
(list 4554.585 396.4439) 
(list 4480.5625 396.1939)))
(apply 'command (append '("pline") coords '("c")))
(setq currobj (ssadd (entlast) currobj))
(setq coords (list 
(list 4480.5625 396.3369) 
(list 4554.585 396.5869) 
(list 4554.585 396.7639) 
(list 4480.5625 396.4139)))
(apply 'command (append '("pline") coords '("c")))
(setq currobj (ssadd (entlast) currobj))
(setq coords (list 
(list 4480.5625 396.5569) 
(list 4554.585 396.9069) 
(list 4554.585 397.0839) 
(list 4480.5625 396.6339)))
(apply 'command (append '("pline") coords '("c")))
(setq currobj (ssadd (entlast) currobj))
(setq coords (list 
(list 4480.5625 396.7769) 
(list 4554.585 397.2269) 
(list 4554.585 397.4039) 
(list 4480.5625 396.8539)))
(apply 'command (append '("pline") coords '("c")))
(setq currobj (ssadd (entlast) currobj))
(setq coords (list 
(list 4480.5625 396.9969) 
(list 4554.585 397.5469) 
(list 4554.585 397.7239) 
(list 4480.5625 397.0739)))
(apply 'command (append '("pline") coords '("c")))
(setq currobj (ssadd (entlast) currobj))
(setq coords (list 
(list 4480.5625 397.2169) 
(list 4554.585 397.8669) 
(list 4554.585 398.0439) 
(list 4480.5625 397.2939)))
(apply 'command (append '("pline") coords '("c")))
(setq currobj (ssadd (entlast) currobj))
(setq coords (list 
(list 4479.4375 397.2939) 
(list 4405.415 398.0439) 
(list 4405.415 397.8669) 
(list 4479.4375 397.2169)))
(apply 'command (append '("pline") coords '("c")))
(setq currobj (ssadd (entlast) currobj))
(setq coords (list 
(list 4479.4375 397.0739) 
(list 4405.415 397.7239) 
(list 4405.415 397.5469) 
(list 4479.4375 396.9969)))
(apply 'command (append '("pline") coords '("c")))
(setq currobj (ssadd (entlast) currobj))
(setq coords (list 
(list 4479.4375 396.8539) 
(list 4405.415 397.4039) 
(list 4405.415 397.2269) 
(list 4479.4375 396.7769)))
(apply 'command (append '("pline") coords '("c")))
(setq currobj (ssadd (entlast) currobj))
(setq coords (list 
(list 4479.4375 396.6339) 
(list 4405.415 397.0839) 
(list 4405.415 396.9069) 
(list 4479.4375 396.5569)))
(apply 'command (append '("pline") coords '("c")))
(setq currobj (ssadd (entlast) currobj))
(setq coords (list 
(list 4479.4375 396.4139) 
(list 4405.415 396.7639) 
(list 4405.415 396.5869) 
(list 4479.4375 396.3369)))
(apply 'command (append '("pline") coords '("c")))
(setq currobj (ssadd (entlast) currobj))
(setq coords (list 
(list 4479.4375 396.1939) 
(list 4405.415 396.4439) 
(list 4405.415 396.2669) 
(list 4479.4375 396.1169)))
(apply 'command (append '("pline") coords '("c")))
(setq currobj (ssadd (entlast) currobj))
(setq coords (list 
(list 4479.4375 395.9739) 
(list 4405.415 396.1239) 
(list 4405.415 395.9469) 
(list 4479.4375 395.8969)))
(apply 'command (append '("pline") coords '("c")))
(setq currobj (ssadd (entlast) currobj))
(setq coords (list 
(list 4479.4375 395.7539) 
(list 4405.415 395.8039) 
(list 4405.415 395.6269) 
(list 4479.4375 395.6769)))
(apply 'command (append '("pline") coords '("c")))
(setq currobj (ssadd (entlast) currobj))
(setq coords (list 
(list 4479.4375 395.5339) 
(list 4405.415 395.4839) 
(list 4405.415 395.3069) 
(list 4479.4375 395.4569)))
(apply 'command (append '("pline") coords '("c")))
(setq currobj (ssadd (entlast) currobj))
(setq coords (list 
(list 4479.4375 395.3139) 
(list 4405.415 395.1639) 
(list 4405.415 394.9869) 
(list 4479.4375 395.2369)))
(apply 'command (append '("pline") coords '("c")))
(setq currobj (ssadd (entlast) currobj))
(setq coords (list 
(list 4479.4375 395.0939) 
(list 4405.415 394.8439) 
(list 4405.415 394.6669) 
(list 4479.4375 395.0169)))
(apply 'command (append '("pline") coords '("c")))
(setq currobj (ssadd (entlast) currobj))
(setq coords (list 
(list 4479.4375 394.8739) 
(list 4405.415 394.5239) 
(list 4405.415 394.3469) 
(list 4479.4375 394.7969)))
(apply 'command (append '("pline") coords '("c")))
(setq currobj (ssadd (entlast) currobj))
(setq coords (list 
(list 4479.4375 394.6539) 
(list 4405.415 394.2039) 
(list 4405.415 394.0269) 
(list 4479.4375 394.5769)))
(apply 'command (append '("pline") coords '("c")))
(setq currobj (ssadd (entlast) currobj))
(setq coords (list 
(list 4479.4375 394.4339) 
(list 4405.415 393.8839) 
(list 4405.415 393.7069) 
(list 4479.4375 394.3569)))
(apply 'command (append '("pline") coords '("c")))
(setq currobj (ssadd (entlast) currobj))
(setq coords (list 
(list 4479.4375 394.2139) 
(list 4405.415 393.5639) 
(list 4405.415 393.3869) 
(list 4479.4375 394.1369)))
(apply 'command (append '("pline") coords '("c")))
(setq currobj (ssadd (entlast) currobj))
(command "_layer" "set" "nitride" "")
(command "_layer" "set" "text" "")
(command "_circle" "4479.0625,382.9939" "0.075")
(command "_circle" "4479.0625,383.2939" "0.075")
(command "_circle" "4479.0625,383.5939" "0.075")
(command "_circle" "4479.0625,383.8939" "0.075")
(command "_circle" "4479.0625,384.1939" "0.075")
(command "_circle" "4478.7625,382.9939" "0.075")
(command "_circle" "4478.7625,383.2939" "0.075")
(command "_circle" "4478.7625,383.5939" "0.075")
(command "_circle" "4478.7625,383.8939" "0.075")
(command "_circle" "4478.7625,384.1939" "0.075")
(command "_circle" "4478.4625,382.9939" "0.075")
(command "_circle" "4478.4625,383.2939" "0.075")
(command "_circle" "4478.4625,383.5939" "0.075")
(command "_circle" "4478.4625,383.8939" "0.075")
(command "_circle" "4478.4625,384.1939" "0.075")
(command "_circle" "4478.1625,382.9939" "0.075")
(command "_circle" "4478.1625,383.2939" "0.075")
(command "_circle" "4478.1625,383.5939" "0.075")
(command "_circle" "4478.1625,383.8939" "0.075")
(command "_circle" "4478.1625,384.1939" "0.075")
(command "_circle" "4477.8625,382.9939" "0.075")
(command "_circle" "4477.8625,383.2939" "0.075")
(command "_circle" "4477.8625,383.5939" "0.075")
(command "_circle" "4477.8625,383.8939" "0.075")
(command "_circle" "4477.8625,384.1939" "0.075")
(command "_layer" "set" "nitride" "")
(setq coords (list 
(list 4480.2625 408.4369) 
(list 4480.2625 524.0816) 
(list 4479.7375 524.0816) 
(list 4479.7375 408.4369)))
(apply 'command (append '("pline") coords '("c")))
(setq currobj (ssadd (entlast) currobj))
(command "_layer" "set" "prebias" "")
(command "_rectangle" "4479.7375,408.4369" "4480.2625,524.0816")
(setq currobj (ssadd (entlast) currobj))
(command "_layer" "set" "nitride" "")
(setq coords (list 
(list 4480.2625 524.0816) 
(list 4480.5625 534.0816) 
(list 4480.5625 534.0816) 
(list 4480.5625 535.0816) 
(list 4554.585 534.3316) 
(list 4554.585 539.2746) 
(list 4480.5625 538.5246) 
(list 4480.5625 539.5246) 
(list 4480.5625 539.5246) 
(list 4480.2625 549.5246) 
(list 4479.7375 549.5246) 
(list 4479.4375 539.5246) 
(list 4479.4375 539.5246) 
(list 4479.4375 538.5246) 
(list 4405.415 539.2746) 
(list 4405.415 534.3316) 
(list 4479.4375 535.0816) 
(list 4479.4375 534.0816) 
(list 4479.4375 534.0816) 
(list 4479.7375 524.0816)))
(apply 'command (append '("pline") coords '("c")))
(setq currobj (ssadd (entlast) currobj))
(command "_layer" "set" "prebias" "")
(setq coords (list 
(list 4479.4375 524.0816) 
(list 4479.4375 535.0816) 
(list 4405.415 534.3316) 
(list 4405.415 539.2746) 
(list 4479.4375 538.5246) 
(list 4479.4375 549.5246) 
(list 4480.5625 549.5246) 
(list 4480.5625 538.5246) 
(list 4554.585 539.2746) 
(list 4554.585 534.3316) 
(list 4480.5625 535.0816) 
(list 4480.5625 524.0816)))
(apply 'command (append '("pline") coords '("c")))
(setq currobj (ssadd (entlast) currobj))
(command "_layer" "set" "nitride" "")
(command "_layer" "set" "fda1" "")
(setq coords (list 
(list 4480.5625 535.2246) 
(list 4554.585 534.4746) 
(list 4554.585 534.6516) 
(list 4480.5625 535.3016)))
(apply 'command (append '("pline") coords '("c")))
(setq currobj (ssadd (entlast) currobj))
(setq coords (list 
(list 4480.5625 535.4446) 
(list 4554.585 534.7946) 
(list 4554.585 534.9716) 
(list 4480.5625 535.5216)))
(apply 'command (append '("pline") coords '("c")))
(setq currobj (ssadd (entlast) currobj))
(setq coords (list 
(list 4480.5625 535.6646) 
(list 4554.585 535.1146) 
(list 4554.585 535.2916) 
(list 4480.5625 535.7416)))
(apply 'command (append '("pline") coords '("c")))
(setq currobj (ssadd (entlast) currobj))
(setq coords (list 
(list 4480.5625 535.8846) 
(list 4554.585 535.4346) 
(list 4554.585 535.6116) 
(list 4480.5625 535.9616)))
(apply 'command (append '("pline") coords '("c")))
(setq currobj (ssadd (entlast) currobj))
(setq coords (list 
(list 4480.5625 536.1046) 
(list 4554.585 535.7546) 
(list 4554.585 535.9316) 
(list 4480.5625 536.1816)))
(apply 'command (append '("pline") coords '("c")))
(setq currobj (ssadd (entlast) currobj))
(setq coords (list 
(list 4480.5625 536.3246) 
(list 4554.585 536.0746) 
(list 4554.585 536.2516) 
(list 4480.5625 536.4016)))
(apply 'command (append '("pline") coords '("c")))
(setq currobj (ssadd (entlast) currobj))
(setq coords (list 
(list 4480.5625 536.5446) 
(list 4554.585 536.3946) 
(list 4554.585 536.5716) 
(list 4480.5625 536.6216)))
(apply 'command (append '("pline") coords '("c")))
(setq currobj (ssadd (entlast) currobj))
(setq coords (list 
(list 4480.5625 536.7646) 
(list 4554.585 536.7146) 
(list 4554.585 536.8916) 
(list 4480.5625 536.8416)))
(apply 'command (append '("pline") coords '("c")))
(setq currobj (ssadd (entlast) currobj))
(setq coords (list 
(list 4480.5625 536.9846) 
(list 4554.585 537.0346) 
(list 4554.585 537.2116) 
(list 4480.5625 537.0616)))
(apply 'command (append '("pline") coords '("c")))
(setq currobj (ssadd (entlast) currobj))
(setq coords (list 
(list 4480.5625 537.2046) 
(list 4554.585 537.3546) 
(list 4554.585 537.5316) 
(list 4480.5625 537.2816)))
(apply 'command (append '("pline") coords '("c")))
(setq currobj (ssadd (entlast) currobj))
(setq coords (list 
(list 4480.5625 537.4246) 
(list 4554.585 537.6746) 
(list 4554.585 537.8516) 
(list 4480.5625 537.5016)))
(apply 'command (append '("pline") coords '("c")))
(setq currobj (ssadd (entlast) currobj))
(setq coords (list 
(list 4480.5625 537.6446) 
(list 4554.585 537.9946) 
(list 4554.585 538.1716) 
(list 4480.5625 537.7216)))
(apply 'command (append '("pline") coords '("c")))
(setq currobj (ssadd (entlast) currobj))
(setq coords (list 
(list 4480.5625 537.8646) 
(list 4554.585 538.3146) 
(list 4554.585 538.4916) 
(list 4480.5625 537.9416)))
(apply 'command (append '("pline") coords '("c")))
(setq currobj (ssadd (entlast) currobj))
(setq coords (list 
(list 4480.5625 538.0846) 
(list 4554.585 538.6346) 
(list 4554.585 538.8116) 
(list 4480.5625 538.1616)))
(apply 'command (append '("pline") coords '("c")))
(setq currobj (ssadd (entlast) currobj))
(setq coords (list 
(list 4480.5625 538.3046) 
(list 4554.585 538.9546) 
(list 4554.585 539.1316) 
(list 4480.5625 538.3816)))
(apply 'command (append '("pline") coords '("c")))
(setq currobj (ssadd (entlast) currobj))
(setq coords (list 
(list 4479.4375 538.3816) 
(list 4405.415 539.1316) 
(list 4405.415 538.9546) 
(list 4479.4375 538.3046)))
(apply 'command (append '("pline") coords '("c")))
(setq currobj (ssadd (entlast) currobj))
(setq coords (list 
(list 4479.4375 538.1616) 
(list 4405.415 538.8116) 
(list 4405.415 538.6346) 
(list 4479.4375 538.0846)))
(apply 'command (append '("pline") coords '("c")))
(setq currobj (ssadd (entlast) currobj))
(setq coords (list 
(list 4479.4375 537.9416) 
(list 4405.415 538.4916) 
(list 4405.415 538.3146) 
(list 4479.4375 537.8646)))
(apply 'command (append '("pline") coords '("c")))
(setq currobj (ssadd (entlast) currobj))
(setq coords (list 
(list 4479.4375 537.7216) 
(list 4405.415 538.1716) 
(list 4405.415 537.9946) 
(list 4479.4375 537.6446)))
(apply 'command (append '("pline") coords '("c")))
(setq currobj (ssadd (entlast) currobj))
(setq coords (list 
(list 4479.4375 537.5016) 
(list 4405.415 537.8516) 
(list 4405.415 537.6746) 
(list 4479.4375 537.4246)))
(apply 'command (append '("pline") coords '("c")))
(setq currobj (ssadd (entlast) currobj))
(setq coords (list 
(list 4479.4375 537.2816) 
(list 4405.415 537.5316) 
(list 4405.415 537.3546) 
(list 4479.4375 537.2046)))
(apply 'command (append '("pline") coords '("c")))
(setq currobj (ssadd (entlast) currobj))
(setq coords (list 
(list 4479.4375 537.0616) 
(list 4405.415 537.2116) 
(list 4405.415 537.0346) 
(list 4479.4375 536.9846)))
(apply 'command (append '("pline") coords '("c")))
(setq currobj (ssadd (entlast) currobj))
(setq coords (list 
(list 4479.4375 536.8416) 
(list 4405.415 536.8916) 
(list 4405.415 536.7146) 
(list 4479.4375 536.7646)))
(apply 'command (append '("pline") coords '("c")))
(setq currobj (ssadd (entlast) currobj))
(setq coords (list 
(list 4479.4375 536.6216) 
(list 4405.415 536.5716) 
(list 4405.415 536.3946) 
(list 4479.4375 536.5446)))
(apply 'command (append '("pline") coords '("c")))
(setq currobj (ssadd (entlast) currobj))
(setq coords (list 
(list 4479.4375 536.4016) 
(list 4405.415 536.2516) 
(list 4405.415 536.0746) 
(list 4479.4375 536.3246)))
(apply 'command (append '("pline") coords '("c")))
(setq currobj (ssadd (entlast) currobj))
(setq coords (list 
(list 4479.4375 536.1816) 
(list 4405.415 535.9316) 
(list 4405.415 535.7546) 
(list 4479.4375 536.1046)))
(apply 'command (append '("pline") coords '("c")))
(setq currobj (ssadd (entlast) currobj))
(setq coords (list 
(list 4479.4375 535.9616) 
(list 4405.415 535.6116) 
(list 4405.415 535.4346) 
(list 4479.4375 535.8846)))
(apply 'command (append '("pline") coords '("c")))
(setq currobj (ssadd (entlast) currobj))
(setq coords (list 
(list 4479.4375 535.7416) 
(list 4405.415 535.2916) 
(list 4405.415 535.1146) 
(list 4479.4375 535.6646)))
(apply 'command (append '("pline") coords '("c")))
(setq currobj (ssadd (entlast) currobj))
(setq coords (list 
(list 4479.4375 535.5216) 
(list 4405.415 534.9716) 
(list 4405.415 534.7946) 
(list 4479.4375 535.4446)))
(apply 'command (append '("pline") coords '("c")))
(setq currobj (ssadd (entlast) currobj))
(setq coords (list 
(list 4479.4375 535.3016) 
(list 4405.415 534.6516) 
(list 4405.415 534.4746) 
(list 4479.4375 535.2246)))
(apply 'command (append '("pline") coords '("c")))
(setq currobj (ssadd (entlast) currobj))
(command "_layer" "set" "nitride" "")
(command "_layer" "set" "text" "")
(command "_circle" "4479.0625,524.0816" "0.075")
(command "_circle" "4479.0625,524.3816" "0.075")
(command "_circle" "4479.0625,524.6816" "0.075")
(command "_circle" "4479.0625,524.9816" "0.075")
(command "_circle" "4479.0625,525.2816" "0.075")
(command "_circle" "4478.7625,524.0816" "0.075")
(command "_circle" "4478.7625,524.3816" "0.075")
(command "_circle" "4478.7625,524.6816" "0.075")
(command "_circle" "4478.7625,524.9816" "0.075")
(command "_circle" "4478.7625,525.2816" "0.075")
(command "_circle" "4478.4625,524.0816" "0.075")
(command "_circle" "4478.4625,524.3816" "0.075")
(command "_circle" "4478.4625,524.6816" "0.075")
(command "_circle" "4478.4625,524.9816" "0.075")
(command "_circle" "4478.4625,525.2816" "0.075")
(command "_circle" "4478.1625,524.0816" "0.075")
(command "_circle" "4478.1625,524.3816" "0.075")
(command "_circle" "4478.1625,524.6816" "0.075")
(command "_circle" "4478.1625,524.9816" "0.075")
(command "_circle" "4478.1625,525.2816" "0.075")
(command "_circle" "4477.8625,524.0816" "0.075")
(command "_circle" "4477.8625,524.3816" "0.075")
(command "_circle" "4477.8625,524.6816" "0.075")
(command "_circle" "4477.8625,524.9816" "0.075")
(command "_circle" "4477.8625,525.2816" "0.075")
(command "_layer" "set" "nitride" "")
(setq coords (list 
(list 4480.2625 549.5246) 
(list 4480.2625 665.1693) 
(list 4479.7375 665.1693) 
(list 4479.7375 549.5246)))
(apply 'command (append '("pline") coords '("c")))
(setq currobj (ssadd (entlast) currobj))
(command "_layer" "set" "prebias" "")
(command "_rectangle" "4479.7375,549.5246" "4480.2625,665.1693")
(setq currobj (ssadd (entlast) currobj))
(command "_layer" "set" "nitride" "")
(setq coords (list 
(list 4480.2625 665.1693) 
(list 4480.5625 675.1693) 
(list 4480.5625 675.1693) 
(list 4480.5625 676.1693) 
(list 4554.585 675.4193) 
(list 4554.585 680.3623) 
(list 4480.5625 679.6123) 
(list 4480.5625 680.6123) 
(list 4480.5625 680.6123) 
(list 4480.2625 690.6123) 
(list 4479.7375 690.6123) 
(list 4479.4375 680.6123) 
(list 4479.4375 680.6123) 
(list 4479.4375 679.6123) 
(list 4405.415 680.3623) 
(list 4405.415 675.4193) 
(list 4479.4375 676.1693) 
(list 4479.4375 675.1693) 
(list 4479.4375 675.1693) 
(list 4479.7375 665.1693)))
(apply 'command (append '("pline") coords '("c")))
(setq currobj (ssadd (entlast) currobj))
(command "_layer" "set" "prebias" "")
(setq coords (list 
(list 4479.4375 665.1693) 
(list 4479.4375 676.1693) 
(list 4405.415 675.4193) 
(list 4405.415 680.3623) 
(list 4479.4375 679.6123) 
(list 4479.4375 690.6123) 
(list 4480.5625 690.6123) 
(list 4480.5625 679.6123) 
(list 4554.585 680.3623) 
(list 4554.585 675.4193) 
(list 4480.5625 676.1693) 
(list 4480.5625 665.1693)))
(apply 'command (append '("pline") coords '("c")))
(setq currobj (ssadd (entlast) currobj))
(command "_layer" "set" "nitride" "")
(command "_layer" "set" "fda1" "")
(setq coords (list 
(list 4480.5625 676.3123) 
(list 4554.585 675.5623) 
(list 4554.585 675.7393) 
(list 4480.5625 676.3893)))
(apply 'command (append '("pline") coords '("c")))
(setq currobj (ssadd (entlast) currobj))
(setq coords (list 
(list 4480.5625 676.5323) 
(list 4554.585 675.8823) 
(list 4554.585 676.0593) 
(list 4480.5625 676.6093)))
(apply 'command (append '("pline") coords '("c")))
(setq currobj (ssadd (entlast) currobj))
(setq coords (list 
(list 4480.5625 676.7523) 
(list 4554.585 676.2023) 
(list 4554.585 676.3793) 
(list 4480.5625 676.8293)))
(apply 'command (append '("pline") coords '("c")))
(setq currobj (ssadd (entlast) currobj))
(setq coords (list 
(list 4480.5625 676.9723) 
(list 4554.585 676.5223) 
(list 4554.585 676.6993) 
(list 4480.5625 677.0493)))
(apply 'command (append '("pline") coords '("c")))
(setq currobj (ssadd (entlast) currobj))
(setq coords (list 
(list 4480.5625 677.1923) 
(list 4554.585 676.8423) 
(list 4554.585 677.0193) 
(list 4480.5625 677.2693)))
(apply 'command (append '("pline") coords '("c")))
(setq currobj (ssadd (entlast) currobj))
(setq coords (list 
(list 4480.5625 677.4123) 
(list 4554.585 677.1623) 
(list 4554.585 677.3393) 
(list 4480.5625 677.4893)))
(apply 'command (append '("pline") coords '("c")))
(setq currobj (ssadd (entlast) currobj))
(setq coords (list 
(list 4480.5625 677.6323) 
(list 4554.585 677.4823) 
(list 4554.585 677.6593) 
(list 4480.5625 677.7093)))
(apply 'command (append '("pline") coords '("c")))
(setq currobj (ssadd (entlast) currobj))
(setq coords (list 
(list 4480.5625 677.8523) 
(list 4554.585 677.8023) 
(list 4554.585 677.9793) 
(list 4480.5625 677.9293)))
(apply 'command (append '("pline") coords '("c")))
(setq currobj (ssadd (entlast) currobj))
(setq coords (list 
(list 4480.5625 678.0723) 
(list 4554.585 678.1223) 
(list 4554.585 678.2993) 
(list 4480.5625 678.1493)))
(apply 'command (append '("pline") coords '("c")))
(setq currobj (ssadd (entlast) currobj))
(setq coords (list 
(list 4480.5625 678.2923) 
(list 4554.585 678.4423) 
(list 4554.585 678.6193) 
(list 4480.5625 678.3693)))
(apply 'command (append '("pline") coords '("c")))
(setq currobj (ssadd (entlast) currobj))
(setq coords (list 
(list 4480.5625 678.5123) 
(list 4554.585 678.7623) 
(list 4554.585 678.9393) 
(list 4480.5625 678.5893)))
(apply 'command (append '("pline") coords '("c")))
(setq currobj (ssadd (entlast) currobj))
(setq coords (list 
(list 4480.5625 678.7323) 
(list 4554.585 679.0823) 
(list 4554.585 679.2593) 
(list 4480.5625 678.8093)))
(apply 'command (append '("pline") coords '("c")))
(setq currobj (ssadd (entlast) currobj))
(setq coords (list 
(list 4480.5625 678.9523) 
(list 4554.585 679.4023) 
(list 4554.585 679.5793) 
(list 4480.5625 679.0293)))
(apply 'command (append '("pline") coords '("c")))
(setq currobj (ssadd (entlast) currobj))
(setq coords (list 
(list 4480.5625 679.1723) 
(list 4554.585 679.7223) 
(list 4554.585 679.8993) 
(list 4480.5625 679.2493)))
(apply 'command (append '("pline") coords '("c")))
(setq currobj (ssadd (entlast) currobj))
(setq coords (list 
(list 4480.5625 679.3923) 
(list 4554.585 680.0423) 
(list 4554.585 680.2193) 
(list 4480.5625 679.4693)))
(apply 'command (append '("pline") coords '("c")))
(setq currobj (ssadd (entlast) currobj))
(setq coords (list 
(list 4479.4375 679.4693) 
(list 4405.415 680.2193) 
(list 4405.415 680.0423) 
(list 4479.4375 679.3923)))
(apply 'command (append '("pline") coords '("c")))
(setq currobj (ssadd (entlast) currobj))
(setq coords (list 
(list 4479.4375 679.2493) 
(list 4405.415 679.8993) 
(list 4405.415 679.7223) 
(list 4479.4375 679.1723)))
(apply 'command (append '("pline") coords '("c")))
(setq currobj (ssadd (entlast) currobj))
(setq coords (list 
(list 4479.4375 679.0293) 
(list 4405.415 679.5793) 
(list 4405.415 679.4023) 
(list 4479.4375 678.9523)))
(apply 'command (append '("pline") coords '("c")))
(setq currobj (ssadd (entlast) currobj))
(setq coords (list 
(list 4479.4375 678.8093) 
(list 4405.415 679.2593) 
(list 4405.415 679.0823) 
(list 4479.4375 678.7323)))
(apply 'command (append '("pline") coords '("c")))
(setq currobj (ssadd (entlast) currobj))
(setq coords (list 
(list 4479.4375 678.5893) 
(list 4405.415 678.9393) 
(list 4405.415 678.7623) 
(list 4479.4375 678.5123)))
(apply 'command (append '("pline") coords '("c")))
(setq currobj (ssadd (entlast) currobj))
(setq coords (list 
(list 4479.4375 678.3693) 
(list 4405.415 678.6193) 
(list 4405.415 678.4423) 
(list 4479.4375 678.2923)))
(apply 'command (append '("pline") coords '("c")))
(setq currobj (ssadd (entlast) currobj))
(setq coords (list 
(list 4479.4375 678.1493) 
(list 4405.415 678.2993) 
(list 4405.415 678.1223) 
(list 4479.4375 678.0723)))
(apply 'command (append '("pline") coords '("c")))
(setq currobj (ssadd (entlast) currobj))
(setq coords (list 
(list 4479.4375 677.9293) 
(list 4405.415 677.9793) 
(list 4405.415 677.8023) 
(list 4479.4375 677.8523)))
(apply 'command (append '("pline") coords '("c")))
(setq currobj (ssadd (entlast) currobj))
(setq coords (list 
(list 4479.4375 677.7093) 
(list 4405.415 677.6593) 
(list 4405.415 677.4823) 
(list 4479.4375 677.6323)))
(apply 'command (append '("pline") coords '("c")))
(setq currobj (ssadd (entlast) currobj))
(setq coords (list 
(list 4479.4375 677.4893) 
(list 4405.415 677.3393) 
(list 4405.415 677.1623) 
(list 4479.4375 677.4123)))
(apply 'command (append '("pline") coords '("c")))
(setq currobj (ssadd (entlast) currobj))
(setq coords (list 
(list 4479.4375 677.2693) 
(list 4405.415 677.0193) 
(list 4405.415 676.8423) 
(list 4479.4375 677.1923)))
(apply 'command (append '("pline") coords '("c")))
(setq currobj (ssadd (entlast) currobj))
(setq coords (list 
(list 4479.4375 677.0493) 
(list 4405.415 676.6993) 
(list 4405.415 676.5223) 
(list 4479.4375 676.9723)))
(apply 'command (append '("pline") coords '("c")))
(setq currobj (ssadd (entlast) currobj))
(setq coords (list 
(list 4479.4375 676.8293) 
(list 4405.415 676.3793) 
(list 4405.415 676.2023) 
(list 4479.4375 676.7523)))
(apply 'command (append '("pline") coords '("c")))
(setq currobj (ssadd (entlast) currobj))
(setq coords (list 
(list 4479.4375 676.6093) 
(list 4405.415 676.0593) 
(list 4405.415 675.8823) 
(list 4479.4375 676.5323)))
(apply 'command (append '("pline") coords '("c")))
(setq currobj (ssadd (entlast) currobj))
(setq coords (list 
(list 4479.4375 676.3893) 
(list 4405.415 675.7393) 
(list 4405.415 675.5623) 
(list 4479.4375 676.3123)))
(apply 'command (append '("pline") coords '("c")))
(setq currobj (ssadd (entlast) currobj))
(command "_layer" "set" "nitride" "")
(command "_layer" "set" "text" "")
(command "_circle" "4479.0625,665.1693" "0.075")
(command "_circle" "4479.0625,665.4693" "0.075")
(command "_circle" "4479.0625,665.7693" "0.075")
(command "_circle" "4479.0625,666.0693" "0.075")
(command "_circle" "4479.0625,666.3693" "0.075")
(command "_circle" "4478.7625,665.1693" "0.075")
(command "_circle" "4478.7625,665.4693" "0.075")
(command "_circle" "4478.7625,665.7693" "0.075")
(command "_circle" "4478.7625,666.0693" "0.075")
(command "_circle" "4478.7625,666.3693" "0.075")
(command "_circle" "4478.4625,665.1693" "0.075")
(command "_circle" "4478.4625,665.4693" "0.075")
(command "_circle" "4478.4625,665.7693" "0.075")
(command "_circle" "4478.4625,666.0693" "0.075")
(command "_circle" "4478.4625,666.3693" "0.075")
(command "_circle" "4478.1625,665.1693" "0.075")
(command "_circle" "4478.1625,665.4693" "0.075")
(command "_circle" "4478.1625,665.7693" "0.075")
(command "_circle" "4478.1625,666.0693" "0.075")
(command "_circle" "4478.1625,666.3693" "0.075")
(command "_circle" "4477.8625,665.1693" "0.075")
(command "_circle" "4477.8625,665.4693" "0.075")
(command "_circle" "4477.8625,665.7693" "0.075")
(command "_circle" "4477.8625,666.0693" "0.075")
(command "_circle" "4477.8625,666.3693" "0.075")
(command "_layer" "set" "nitride" "")
(setq coords (list 
(list 4480.2625 690.6123) 
(list 4480.2625 806.257) 
(list 4479.7375 806.257) 
(list 4479.7375 690.6123)))
(apply 'command (append '("pline") coords '("c")))
(setq currobj (ssadd (entlast) currobj))
(command "_layer" "set" "prebias" "")
(command "_rectangle" "4479.7375,690.6123" "4480.2625,806.257")
(setq currobj (ssadd (entlast) currobj))
(command "_layer" "set" "nitride" "")
(setq coords (list 
(list 4480.2625 806.257) 
(list 4480.5625 816.257) 
(list 4480.5625 816.257) 
(list 4480.5625 817.257) 
(list 4554.585 816.507) 
(list 4554.585 821.45) 
(list 4480.5625 820.7) 
(list 4480.5625 821.7) 
(list 4480.5625 821.7) 
(list 4480.2625 831.7) 
(list 4479.7375 831.7) 
(list 4479.4375 821.7) 
(list 4479.4375 821.7) 
(list 4479.4375 820.7) 
(list 4405.415 821.45) 
(list 4405.415 816.507) 
(list 4479.4375 817.257) 
(list 4479.4375 816.257) 
(list 4479.4375 816.257) 
(list 4479.7375 806.257)))
(apply 'command (append '("pline") coords '("c")))
(setq currobj (ssadd (entlast) currobj))
(command "_layer" "set" "prebias" "")
(setq coords (list 
(list 4479.4375 806.257) 
(list 4479.4375 817.257) 
(list 4405.415 816.507) 
(list 4405.415 821.45) 
(list 4479.4375 820.7) 
(list 4479.4375 831.7) 
(list 4480.5625 831.7) 
(list 4480.5625 820.7) 
(list 4554.585 821.45) 
(list 4554.585 816.507) 
(list 4480.5625 817.257) 
(list 4480.5625 806.257)))
(apply 'command (append '("pline") coords '("c")))
(setq currobj (ssadd (entlast) currobj))
(command "_layer" "set" "nitride" "")
(command "_layer" "set" "fda1" "")
(setq coords (list 
(list 4480.5625 817.4) 
(list 4554.585 816.65) 
(list 4554.585 816.827) 
(list 4480.5625 817.477)))
(apply 'command (append '("pline") coords '("c")))
(setq currobj (ssadd (entlast) currobj))
(setq coords (list 
(list 4480.5625 817.62) 
(list 4554.585 816.97) 
(list 4554.585 817.147) 
(list 4480.5625 817.697)))
(apply 'command (append '("pline") coords '("c")))
(setq currobj (ssadd (entlast) currobj))
(setq coords (list 
(list 4480.5625 817.84) 
(list 4554.585 817.29) 
(list 4554.585 817.467) 
(list 4480.5625 817.917)))
(apply 'command (append '("pline") coords '("c")))
(setq currobj (ssadd (entlast) currobj))
(setq coords (list 
(list 4480.5625 818.06) 
(list 4554.585 817.61) 
(list 4554.585 817.787) 
(list 4480.5625 818.137)))
(apply 'command (append '("pline") coords '("c")))
(setq currobj (ssadd (entlast) currobj))
(setq coords (list 
(list 4480.5625 818.28) 
(list 4554.585 817.93) 
(list 4554.585 818.107) 
(list 4480.5625 818.357)))
(apply 'command (append '("pline") coords '("c")))
(setq currobj (ssadd (entlast) currobj))
(setq coords (list 
(list 4480.5625 818.5) 
(list 4554.585 818.25) 
(list 4554.585 818.427) 
(list 4480.5625 818.577)))
(apply 'command (append '("pline") coords '("c")))
(setq currobj (ssadd (entlast) currobj))
(setq coords (list 
(list 4480.5625 818.72) 
(list 4554.585 818.57) 
(list 4554.585 818.747) 
(list 4480.5625 818.797)))
(apply 'command (append '("pline") coords '("c")))
(setq currobj (ssadd (entlast) currobj))
(setq coords (list 
(list 4480.5625 818.94) 
(list 4554.585 818.89) 
(list 4554.585 819.067) 
(list 4480.5625 819.017)))
(apply 'command (append '("pline") coords '("c")))
(setq currobj (ssadd (entlast) currobj))
(setq coords (list 
(list 4480.5625 819.16) 
(list 4554.585 819.21) 
(list 4554.585 819.387) 
(list 4480.5625 819.237)))
(apply 'command (append '("pline") coords '("c")))
(setq currobj (ssadd (entlast) currobj))
(setq coords (list 
(list 4480.5625 819.38) 
(list 4554.585 819.53) 
(list 4554.585 819.707) 
(list 4480.5625 819.457)))
(apply 'command (append '("pline") coords '("c")))
(setq currobj (ssadd (entlast) currobj))
(setq coords (list 
(list 4480.5625 819.6) 
(list 4554.585 819.85) 
(list 4554.585 820.027) 
(list 4480.5625 819.677)))
(apply 'command (append '("pline") coords '("c")))
(setq currobj (ssadd (entlast) currobj))
(setq coords (list 
(list 4480.5625 819.82) 
(list 4554.585 820.17) 
(list 4554.585 820.347) 
(list 4480.5625 819.897)))
(apply 'command (append '("pline") coords '("c")))
(setq currobj (ssadd (entlast) currobj))
(setq coords (list 
(list 4480.5625 820.04) 
(list 4554.585 820.49) 
(list 4554.585 820.667) 
(list 4480.5625 820.117)))
(apply 'command (append '("pline") coords '("c")))
(setq currobj (ssadd (entlast) currobj))
(setq coords (list 
(list 4480.5625 820.26) 
(list 4554.585 820.81) 
(list 4554.585 820.987) 
(list 4480.5625 820.337)))
(apply 'command (append '("pline") coords '("c")))
(setq currobj (ssadd (entlast) currobj))
(setq coords (list 
(list 4480.5625 820.48) 
(list 4554.585 821.13) 
(list 4554.585 821.307) 
(list 4480.5625 820.557)))
(apply 'command (append '("pline") coords '("c")))
(setq currobj (ssadd (entlast) currobj))
(setq coords (list 
(list 4479.4375 820.557) 
(list 4405.415 821.307) 
(list 4405.415 821.13) 
(list 4479.4375 820.48)))
(apply 'command (append '("pline") coords '("c")))
(setq currobj (ssadd (entlast) currobj))
(setq coords (list 
(list 4479.4375 820.337) 
(list 4405.415 820.987) 
(list 4405.415 820.81) 
(list 4479.4375 820.26)))
(apply 'command (append '("pline") coords '("c")))
(setq currobj (ssadd (entlast) currobj))
(setq coords (list 
(list 4479.4375 820.117) 
(list 4405.415 820.667) 
(list 4405.415 820.49) 
(list 4479.4375 820.04)))
(apply 'command (append '("pline") coords '("c")))
(setq currobj (ssadd (entlast) currobj))
(setq coords (list 
(list 4479.4375 819.897) 
(list 4405.415 820.347) 
(list 4405.415 820.17) 
(list 4479.4375 819.82)))
(apply 'command (append '("pline") coords '("c")))
(setq currobj (ssadd (entlast) currobj))
(setq coords (list 
(list 4479.4375 819.677) 
(list 4405.415 820.027) 
(list 4405.415 819.85) 
(list 4479.4375 819.6)))
(apply 'command (append '("pline") coords '("c")))
(setq currobj (ssadd (entlast) currobj))
(setq coords (list 
(list 4479.4375 819.457) 
(list 4405.415 819.707) 
(list 4405.415 819.53) 
(list 4479.4375 819.38)))
(apply 'command (append '("pline") coords '("c")))
(setq currobj (ssadd (entlast) currobj))
(setq coords (list 
(list 4479.4375 819.237) 
(list 4405.415 819.387) 
(list 4405.415 819.21) 
(list 4479.4375 819.16)))
(apply 'command (append '("pline") coords '("c")))
(setq currobj (ssadd (entlast) currobj))
(setq coords (list 
(list 4479.4375 819.017) 
(list 4405.415 819.067) 
(list 4405.415 818.89) 
(list 4479.4375 818.94)))
(apply 'command (append '("pline") coords '("c")))
(setq currobj (ssadd (entlast) currobj))
(setq coords (list 
(list 4479.4375 818.797) 
(list 4405.415 818.747) 
(list 4405.415 818.57) 
(list 4479.4375 818.72)))
(apply 'command (append '("pline") coords '("c")))
(setq currobj (ssadd (entlast) currobj))
(setq coords (list 
(list 4479.4375 818.577) 
(list 4405.415 818.427) 
(list 4405.415 818.25) 
(list 4479.4375 818.5)))
(apply 'command (append '("pline") coords '("c")))
(setq currobj (ssadd (entlast) currobj))
(setq coords (list 
(list 4479.4375 818.357) 
(list 4405.415 818.107) 
(list 4405.415 817.93) 
(list 4479.4375 818.28)))
(apply 'command (append '("pline") coords '("c")))
(setq currobj (ssadd (entlast) currobj))
(setq coords (list 
(list 4479.4375 818.137) 
(list 4405.415 817.787) 
(list 4405.415 817.61) 
(list 4479.4375 818.06)))
(apply 'command (append '("pline") coords '("c")))
(setq currobj (ssadd (entlast) currobj))
(setq coords (list 
(list 4479.4375 817.917) 
(list 4405.415 817.467) 
(list 4405.415 817.29) 
(list 4479.4375 817.84)))
(apply 'command (append '("pline") coords '("c")))
(setq currobj (ssadd (entlast) currobj))
(setq coords (list 
(list 4479.4375 817.697) 
(list 4405.415 817.147) 
(list 4405.415 816.97) 
(list 4479.4375 817.62)))
(apply 'command (append '("pline") coords '("c")))
(setq currobj (ssadd (entlast) currobj))
(setq coords (list 
(list 4479.4375 817.477) 
(list 4405.415 816.827) 
(list 4405.415 816.65) 
(list 4479.4375 817.4)))
(apply 'command (append '("pline") coords '("c")))
(setq currobj (ssadd (entlast) currobj))
(command "_layer" "set" "nitride" "")
(command "_layer" "set" "text" "")
(command "_circle" "4479.0625,806.257" "0.075")
(command "_circle" "4479.0625,806.557" "0.075")
(command "_circle" "4479.0625,806.857" "0.075")
(command "_circle" "4479.0625,807.157" "0.075")
(command "_circle" "4479.0625,807.457" "0.075")
(command "_circle" "4478.7625,806.257" "0.075")
(command "_circle" "4478.7625,806.557" "0.075")
(command "_circle" "4478.7625,806.857" "0.075")
(command "_circle" "4478.7625,807.157" "0.075")
(command "_circle" "4478.7625,807.457" "0.075")
(command "_circle" "4478.4625,806.257" "0.075")
(command "_circle" "4478.4625,806.557" "0.075")
(command "_circle" "4478.4625,806.857" "0.075")
(command "_circle" "4478.4625,807.157" "0.075")
(command "_circle" "4478.4625,807.457" "0.075")
(command "_circle" "4478.1625,806.257" "0.075")
(command "_circle" "4478.1625,806.557" "0.075")
(command "_circle" "4478.1625,806.857" "0.075")
(command "_circle" "4478.1625,807.157" "0.075")
(command "_circle" "4478.1625,807.457" "0.075")
(command "_circle" "4477.8625,806.257" "0.075")
(command "_circle" "4477.8625,806.557" "0.075")
(command "_circle" "4477.8625,806.857" "0.075")
(command "_circle" "4477.8625,807.157" "0.075")
(command "_circle" "4477.8625,807.457" "0.075")
(command "_layer" "set" "nitride" "")
(setq coords (list 
(list 4480.2625 831.7) 
(list 4480.2625 836.7) 
(list 4479.7375 836.7) 
(list 4479.7375 831.7)))
(apply 'command (append '("pline") coords '("c")))
(setq currobj (ssadd (entlast) currobj))
(command "_layer" "set" "prebias" "")
(command "_rectangle" "4479.7375,831.7" "4480.2625,836.7")
(setq currobj (ssadd (entlast) currobj))
(command "_layer" "set" "nitride" "")
(setq cooledsinglenanobeam14 currobj)
(setq currobj nil)
(setq currobj (ssadd))
; DRAWING PHOTONIC CRYSTAL
(command "_layer" "set" "negYjunc" "")
(setq coords (list 
(list 4480.135 866.7) 
(list 4480 851.7) 
(list 4480 866.7)))
(apply 'command (append '("pline") coords '("c")))
(setq currobj (ssadd (entlast) currobj))
(setq coords (list 
(list 4480.2625 836.7) 
(list 4480.415 866.7) 
(list 4481.135 866.7) 
(list 4481.135 836.7)))
(apply 'command (append '("pline") coords '("c")))
(setq currobj (ssadd (entlast) currobj))
(setq coords (list 
(list 4479.865 866.7) 
(list 4480 851.7) 
(list 4480 866.7)))
(apply 'command (append '("pline") coords '("c")))
(setq currobj (ssadd (entlast) currobj))
(setq coords (list 
(list 4479.7375 836.7) 
(list 4479.585 866.7) 
(list 4478.865 866.7) 
(list 4478.865 836.7)))
(apply 'command (append '("pline") coords '("c")))
(setq currobj (ssadd (entlast) currobj))
(command "_layer" "set" "nitride" "")
(setq yjunction14 currobj)
(setq currobj nil)
(setq currobj (ssadd))
(setq tap14 nil)
(setq tap14 (ssadd))
(command "_layer" "set" "phc" "")
(setq coords (list 
(list 4480 866.7) 
(list 4480.135 866.7) 
(list 4480.135 866.7103) 
(list 4480.135 866.7206) 
(list 4480.135 866.7308) 
(list 4480.135 866.7411) 
(list 4480.135 866.7514) 
(list 4480.135 866.7617) 
(list 4480.135 866.7719) 
(list 4480.135 866.7822) 
(list 4480.135 866.7925) 
(list 4480.135 866.8028) 
(list 4480.135 866.8131) 
(list 4480.135 866.8233) 
(list 4480.135 866.8336) 
(list 4480.135 866.8439) 
(list 4480.135 866.8542) 
(list 4480.135 866.8644) 
(list 4480.135 866.8747) 
(list 4480.135 866.885) 
(list 4480.135 866.8953) 
(list 4480.135 866.9056) 
(list 4480.135 866.9158) 
(list 4480.135 866.9261) 
(list 4480.135 866.9364) 
(list 4480.135 866.9467) 
(list 4480.135 866.9569) 
(list 4480.135 866.9672) 
(list 4480.135 866.9775) 
(list 4480.135 866.9878) 
(list 4480.135 866.9981) 
(list 4480.135 867.0083) 
(list 4480.135 867.0186) 
(list 4480.135 867.0289) 
(list 4480.135 867.0392) 
(list 4480.135 867.0494) 
(list 4480.135 867.0597) 
(list 4480.135 867.07) 
(list 4480 867.07)))
(apply 'command (append '("pline") coords '("c")))
(setq tap14 (ssadd (entlast) tap14))
(command "_mirror" (entlast) "" "4480,900" "4480,901" "No")
(setq tap14 (ssadd (entlast) tap14))
(setq coords (list 
(list 4480.4252 866.7) 
(list 4480.415 866.7) 
(list 4480.4153 866.7103) 
(list 4480.4155 866.7206) 
(list 4480.4157 866.7308) 
(list 4480.4159 866.7411) 
(list 4480.416 866.7514) 
(list 4480.4159 866.7617) 
(list 4480.4158 866.7719) 
(list 4480.4156 866.7822) 
(list 4480.4153 866.7925) 
(list 4480.4149 866.8028) 
(list 4480.4144 866.8131) 
(list 4480.4139 866.8233) 
(list 4480.4134 866.8336) 
(list 4480.4128 866.8439) 
(list 4480.4123 866.8542) 
(list 4480.4118 866.8644) 
(list 4480.4114 866.8747) 
(list 4480.4111 866.885) 
(list 4480.411 866.8953) 
(list 4480.411 866.9056) 
(list 4480.4112 866.9158) 
(list 4480.4115 866.9261) 
(list 4480.4121 866.9364) 
(list 4480.4128 866.9467) 
(list 4480.4137 866.9569) 
(list 4480.4147 866.9672) 
(list 4480.4159 866.9775) 
(list 4480.4171 866.9878) 
(list 4480.4184 866.9981) 
(list 4480.4197 867.0083) 
(list 4480.421 867.0186) 
(list 4480.4222 867.0289) 
(list 4480.4232 867.0392) 
(list 4480.4241 867.0494) 
(list 4480.4248 867.0597) 
(list 4480.4252 867.07) 
(list 4480.4252 867.07)))
(apply 'command (append '("pline") coords '("c")))
(setq tap14 (ssadd (entlast) tap14))
(command "_mirror" (entlast) "" "4480,900" "4480,901" "No")
(setq tap14 (ssadd (entlast) tap14))
(setq coords (list 
(list 4481.135 866.7) 
(list 4480.4252 866.7) 
(list 4480.4252 866.7103) 
(list 4480.4252 866.7206) 
(list 4480.4252 866.7308) 
(list 4480.4252 866.7411) 
(list 4480.4252 866.7514) 
(list 4480.4252 866.7617) 
(list 4480.4252 866.7719) 
(list 4480.4252 866.7822) 
(list 4480.4252 866.7925) 
(list 4480.4252 866.8028) 
(list 4480.4252 866.8131) 
(list 4480.4252 866.8233) 
(list 4480.4252 866.8336) 
(list 4480.4252 866.8439) 
(list 4480.4252 866.8542) 
(list 4480.4252 866.8644) 
(list 4480.4252 866.8747) 
(list 4480.4252 866.885) 
(list 4480.4252 866.8953) 
(list 4480.4252 866.9056) 
(list 4480.4252 866.9158) 
(list 4480.4252 866.9261) 
(list 4480.4252 866.9364) 
(list 4480.4252 866.9467) 
(list 4480.4252 866.9569) 
(list 4480.4252 866.9672) 
(list 4480.4252 866.9775) 
(list 4480.4252 866.9878) 
(list 4480.4252 866.9981) 
(list 4480.4252 867.0083) 
(list 4480.4252 867.0186) 
(list 4480.4252 867.0289) 
(list 4480.4252 867.0392) 
(list 4480.4252 867.0494) 
(list 4480.4252 867.0597) 
(list 4480.4252 867.07) 
(list 4481.135 867.07)))
(apply 'command (append '("pline") coords '("c")))
(setq tap14 (ssadd (entlast) tap14))
(command "_mirror" (entlast) "" "4480,900" "4480,901" "No")
(setq tap14 (ssadd (entlast) tap14))
(setq coords (list 
(list 4480 867.07) 
(list 4480.135 867.07) 
(list 4480.135 867.0803) 
(list 4480.135 867.0906) 
(list 4480.135 867.1008) 
(list 4480.135 867.1111) 
(list 4480.135 867.1214) 
(list 4480.135 867.1317) 
(list 4480.135 867.1419) 
(list 4480.135 867.1522) 
(list 4480.135 867.1625) 
(list 4480.135 867.1728) 
(list 4480.135 867.1831) 
(list 4480.135 867.1933) 
(list 4480.135 867.2036) 
(list 4480.135 867.2139) 
(list 4480.135 867.2242) 
(list 4480.135 867.2344) 
(list 4480.135 867.2447) 
(list 4480.135 867.255) 
(list 4480.135 867.2653) 
(list 4480.135 867.2756) 
(list 4480.135 867.2858) 
(list 4480.135 867.2961) 
(list 4480.135 867.3064) 
(list 4480.135 867.3167) 
(list 4480.135 867.3269) 
(list 4480.135 867.3372) 
(list 4480.135 867.3475) 
(list 4480.135 867.3578) 
(list 4480.135 867.3681) 
(list 4480.135 867.3783) 
(list 4480.135 867.3886) 
(list 4480.135 867.3989) 
(list 4480.135 867.4092) 
(list 4480.135 867.4194) 
(list 4480.135 867.4297) 
(list 4480.135 867.44) 
(list 4480 867.44)))
(apply 'command (append '("pline") coords '("c")))
(setq tap14 (ssadd (entlast) tap14))
(command "_mirror" (entlast) "" "4480,900" "4480,901" "No")
(setq tap14 (ssadd (entlast) tap14))
(setq coords (list 
(list 4480.4353 867.07) 
(list 4480.4252 867.07) 
(list 4480.4253 867.0803) 
(list 4480.4252 867.0906) 
(list 4480.4247 867.1008) 
(list 4480.424 867.1111) 
(list 4480.4229 867.1214) 
(list 4480.4216 867.1317) 
(list 4480.4201 867.1419) 
(list 4480.4184 867.1522) 
(list 4480.4165 867.1625) 
(list 4480.4145 867.1728) 
(list 4480.4126 867.1831) 
(list 4480.4106 867.1933) 
(list 4480.4088 867.2036) 
(list 4480.4071 867.2139) 
(list 4480.4057 867.2242) 
(list 4480.4046 867.2344) 
(list 4480.4038 867.2447) 
(list 4480.4033 867.255) 
(list 4480.4033 867.2653) 
(list 4480.4038 867.2756) 
(list 4480.4046 867.2858) 
(list 4480.4059 867.2961) 
(list 4480.4075 867.3064) 
(list 4480.4095 867.3167) 
(list 4480.4118 867.3269) 
(list 4480.4144 867.3372) 
(list 4480.4171 867.3475) 
(list 4480.4199 867.3578) 
(list 4480.4227 867.3681) 
(list 4480.4254 867.3783) 
(list 4480.428 867.3886) 
(list 4480.4302 867.3989) 
(list 4480.4322 867.4092) 
(list 4480.4337 867.4194) 
(list 4480.4348 867.4297) 
(list 4480.4353 867.44) 
(list 4480.4353 867.44)))
(apply 'command (append '("pline") coords '("c")))
(setq tap14 (ssadd (entlast) tap14))
(command "_mirror" (entlast) "" "4480,900" "4480,901" "No")
(setq tap14 (ssadd (entlast) tap14))
(setq coords (list 
(list 4481.135 867.07) 
(list 4480.4353 867.07) 
(list 4480.4353 867.0803) 
(list 4480.4353 867.0906) 
(list 4480.4353 867.1008) 
(list 4480.4353 867.1111) 
(list 4480.4353 867.1214) 
(list 4480.4353 867.1317) 
(list 4480.4353 867.1419) 
(list 4480.4353 867.1522) 
(list 4480.4353 867.1625) 
(list 4480.4353 867.1728) 
(list 4480.4353 867.1831) 
(list 4480.4353 867.1933) 
(list 4480.4353 867.2036) 
(list 4480.4353 867.2139) 
(list 4480.4353 867.2242) 
(list 4480.4353 867.2344) 
(list 4480.4353 867.2447) 
(list 4480.4353 867.255) 
(list 4480.4353 867.2653) 
(list 4480.4353 867.2756) 
(list 4480.4353 867.2858) 
(list 4480.4353 867.2961) 
(list 4480.4353 867.3064) 
(list 4480.4353 867.3167) 
(list 4480.4353 867.3269) 
(list 4480.4353 867.3372) 
(list 4480.4353 867.3475) 
(list 4480.4353 867.3578) 
(list 4480.4353 867.3681) 
(list 4480.4353 867.3783) 
(list 4480.4353 867.3886) 
(list 4480.4353 867.3989) 
(list 4480.4353 867.4092) 
(list 4480.4353 867.4194) 
(list 4480.4353 867.4297) 
(list 4480.4353 867.44) 
(list 4481.135 867.44)))
(apply 'command (append '("pline") coords '("c")))
(setq tap14 (ssadd (entlast) tap14))
(command "_mirror" (entlast) "" "4480,900" "4480,901" "No")
(setq tap14 (ssadd (entlast) tap14))
(setq coords (list 
(list 4480 867.44) 
(list 4480.135 867.44) 
(list 4480.135 867.4503) 
(list 4480.135 867.4606) 
(list 4480.135 867.4708) 
(list 4480.135 867.4811) 
(list 4480.135 867.4914) 
(list 4480.135 867.5017) 
(list 4480.135 867.5119) 
(list 4480.135 867.5222) 
(list 4480.135 867.5325) 
(list 4480.135 867.5428) 
(list 4480.135 867.5531) 
(list 4480.135 867.5633) 
(list 4480.135 867.5736) 
(list 4480.135 867.5839) 
(list 4480.135 867.5942) 
(list 4480.135 867.6044) 
(list 4480.135 867.6147) 
(list 4480.135 867.625) 
(list 4480.135 867.6353) 
(list 4480.135 867.6456) 
(list 4480.135 867.6558) 
(list 4480.135 867.6661) 
(list 4480.135 867.6764) 
(list 4480.135 867.6867) 
(list 4480.135 867.6969) 
(list 4480.135 867.7072) 
(list 4480.135 867.7175) 
(list 4480.135 867.7278) 
(list 4480.135 867.7381) 
(list 4480.135 867.7483) 
(list 4480.135 867.7586) 
(list 4480.135 867.7689) 
(list 4480.135 867.7792) 
(list 4480.135 867.7894) 
(list 4480.135 867.7997) 
(list 4480.135 867.81) 
(list 4480 867.81)))
(apply 'command (append '("pline") coords '("c")))
(setq tap14 (ssadd (entlast) tap14))
(command "_mirror" (entlast) "" "4480,900" "4480,901" "No")
(setq tap14 (ssadd (entlast) tap14))
(setq coords (list 
(list 4480.4455 867.44) 
(list 4480.4353 867.44) 
(list 4480.4353 867.4503) 
(list 4480.4348 867.4606) 
(list 4480.4337 867.4708) 
(list 4480.432 867.4811) 
(list 4480.4299 867.4914) 
(list 4480.4273 867.5017) 
(list 4480.4244 867.5119) 
(list 4480.4211 867.5222) 
(list 4480.4177 867.5325) 
(list 4480.4142 867.5428) 
(list 4480.4107 867.5531) 
(list 4480.4073 867.5633) 
(list 4480.4042 867.5736) 
(list 4480.4015 867.5839) 
(list 4480.3991 867.5942) 
(list 4480.3973 867.6044) 
(list 4480.3961 867.6147) 
(list 4480.3956 867.625) 
(list 4480.3957 867.6353) 
(list 4480.3965 867.6456) 
(list 4480.398 867.6558) 
(list 4480.4002 867.6661) 
(list 4480.403 867.6764) 
(list 4480.4062 867.6867) 
(list 4480.41 867.6969) 
(list 4480.414 867.7072) 
(list 4480.4183 867.7175) 
(list 4480.4227 867.7278) 
(list 4480.427 867.7381) 
(list 4480.4311 867.7483) 
(list 4480.4349 867.7586) 
(list 4480.4383 867.7689) 
(list 4480.4411 867.7792) 
(list 4480.4433 867.7894) 
(list 4480.4448 867.7997) 
(list 4480.4455 867.81) 
(list 4480.4455 867.81)))
(apply 'command (append '("pline") coords '("c")))
(setq tap14 (ssadd (entlast) tap14))
(command "_mirror" (entlast) "" "4480,900" "4480,901" "No")
(setq tap14 (ssadd (entlast) tap14))
(setq coords (list 
(list 4481.135 867.44) 
(list 4480.4455 867.44) 
(list 4480.4455 867.4503) 
(list 4480.4455 867.4606) 
(list 4480.4455 867.4708) 
(list 4480.4455 867.4811) 
(list 4480.4455 867.4914) 
(list 4480.4455 867.5017) 
(list 4480.4455 867.5119) 
(list 4480.4455 867.5222) 
(list 4480.4455 867.5325) 
(list 4480.4455 867.5428) 
(list 4480.4455 867.5531) 
(list 4480.4455 867.5633) 
(list 4480.4455 867.5736) 
(list 4480.4455 867.5839) 
(list 4480.4455 867.5942) 
(list 4480.4455 867.6044) 
(list 4480.4455 867.6147) 
(list 4480.4455 867.625) 
(list 4480.4455 867.6353) 
(list 4480.4455 867.6456) 
(list 4480.4455 867.6558) 
(list 4480.4455 867.6661) 
(list 4480.4455 867.6764) 
(list 4480.4455 867.6867) 
(list 4480.4455 867.6969) 
(list 4480.4455 867.7072) 
(list 4480.4455 867.7175) 
(list 4480.4455 867.7278) 
(list 4480.4455 867.7381) 
(list 4480.4455 867.7483) 
(list 4480.4455 867.7586) 
(list 4480.4455 867.7689) 
(list 4480.4455 867.7792) 
(list 4480.4455 867.7894) 
(list 4480.4455 867.7997) 
(list 4480.4455 867.81) 
(list 4481.135 867.81)))
(apply 'command (append '("pline") coords '("c")))
(setq tap14 (ssadd (entlast) tap14))
(command "_mirror" (entlast) "" "4480,900" "4480,901" "No")
(setq tap14 (ssadd (entlast) tap14))
(setq coords (list 
(list 4480 867.81) 
(list 4480.135 867.81) 
(list 4480.135 867.8203) 
(list 4480.135 867.8306) 
(list 4480.135 867.8408) 
(list 4480.135 867.8511) 
(list 4480.135 867.8614) 
(list 4480.135 867.8717) 
(list 4480.135 867.8819) 
(list 4480.135 867.8922) 
(list 4480.135 867.9025) 
(list 4480.135 867.9128) 
(list 4480.135 867.9231) 
(list 4480.135 867.9333) 
(list 4480.135 867.9436) 
(list 4480.135 867.9539) 
(list 4480.135 867.9642) 
(list 4480.135 867.9744) 
(list 4480.135 867.9847) 
(list 4480.135 867.995) 
(list 4480.135 868.0053) 
(list 4480.135 868.0156) 
(list 4480.135 868.0258) 
(list 4480.135 868.0361) 
(list 4480.135 868.0464) 
(list 4480.135 868.0567) 
(list 4480.135 868.0669) 
(list 4480.135 868.0772) 
(list 4480.135 868.0875) 
(list 4480.135 868.0978) 
(list 4480.135 868.1081) 
(list 4480.135 868.1183) 
(list 4480.135 868.1286) 
(list 4480.135 868.1389) 
(list 4480.135 868.1492) 
(list 4480.135 868.1594) 
(list 4480.135 868.1697) 
(list 4480.135 868.18) 
(list 4480 868.18)))
(apply 'command (append '("pline") coords '("c")))
(setq tap14 (ssadd (entlast) tap14))
(command "_mirror" (entlast) "" "4480,900" "4480,901" "No")
(setq tap14 (ssadd (entlast) tap14))
(setq coords (list 
(list 4480.4557 867.81) 
(list 4480.4455 867.81) 
(list 4480.4454 867.8203) 
(list 4480.4444 867.8306) 
(list 4480.4426 867.8408) 
(list 4480.4401 867.8511) 
(list 4480.4369 867.8614) 
(list 4480.433 867.8717) 
(list 4480.4286 867.8819) 
(list 4480.4239 867.8922) 
(list 4480.4189 867.9025) 
(list 4480.4138 867.9128) 
(list 4480.4088 867.9231) 
(list 4480.4041 867.9333) 
(list 4480.3997 867.9436) 
(list 4480.3958 867.9539) 
(list 4480.3926 867.9642) 
(list 4480.3901 867.9744) 
(list 4480.3885 867.9847) 
(list 4480.3878 867.995) 
(list 4480.3881 868.0053) 
(list 4480.3893 868.0156) 
(list 4480.3915 868.0258) 
(list 4480.3945 868.0361) 
(list 4480.3984 868.0464) 
(list 4480.403 868.0567) 
(list 4480.4081 868.0669) 
(list 4480.4137 868.0772) 
(list 4480.4195 868.0875) 
(list 4480.4254 868.0978) 
(list 4480.4312 868.1081) 
(list 4480.4368 868.1183) 
(list 4480.4419 868.1286) 
(list 4480.4464 868.1389) 
(list 4480.4501 868.1492) 
(list 4480.453 868.1594) 
(list 4480.4548 868.1697) 
(list 4480.4557 868.18) 
(list 4480.4557 868.18)))
(apply 'command (append '("pline") coords '("c")))
(setq tap14 (ssadd (entlast) tap14))
(command "_mirror" (entlast) "" "4480,900" "4480,901" "No")
(setq tap14 (ssadd (entlast) tap14))
(setq coords (list 
(list 4481.135 867.81) 
(list 4480.4557 867.81) 
(list 4480.4557 867.8203) 
(list 4480.4557 867.8306) 
(list 4480.4557 867.8408) 
(list 4480.4557 867.8511) 
(list 4480.4557 867.8614) 
(list 4480.4557 867.8717) 
(list 4480.4557 867.8819) 
(list 4480.4557 867.8922) 
(list 4480.4557 867.9025) 
(list 4480.4557 867.9128) 
(list 4480.4557 867.9231) 
(list 4480.4557 867.9333) 
(list 4480.4557 867.9436) 
(list 4480.4557 867.9539) 
(list 4480.4557 867.9642) 
(list 4480.4557 867.9744) 
(list 4480.4557 867.9847) 
(list 4480.4557 867.995) 
(list 4480.4557 868.0053) 
(list 4480.4557 868.0156) 
(list 4480.4557 868.0258) 
(list 4480.4557 868.0361) 
(list 4480.4557 868.0464) 
(list 4480.4557 868.0567) 
(list 4480.4557 868.0669) 
(list 4480.4557 868.0772) 
(list 4480.4557 868.0875) 
(list 4480.4557 868.0978) 
(list 4480.4557 868.1081) 
(list 4480.4557 868.1183) 
(list 4480.4557 868.1286) 
(list 4480.4557 868.1389) 
(list 4480.4557 868.1492) 
(list 4480.4557 868.1594) 
(list 4480.4557 868.1697) 
(list 4480.4557 868.18) 
(list 4481.135 868.18)))
(apply 'command (append '("pline") coords '("c")))
(setq tap14 (ssadd (entlast) tap14))
(command "_mirror" (entlast) "" "4480,900" "4480,901" "No")
(setq tap14 (ssadd (entlast) tap14))
(setq coords (list 
(list 4480 868.18) 
(list 4480.135 868.18) 
(list 4480.135 868.1903) 
(list 4480.135 868.2006) 
(list 4480.135 868.2108) 
(list 4480.135 868.2211) 
(list 4480.135 868.2314) 
(list 4480.135 868.2417) 
(list 4480.135 868.2519) 
(list 4480.135 868.2622) 
(list 4480.135 868.2725) 
(list 4480.135 868.2828) 
(list 4480.135 868.2931) 
(list 4480.135 868.3033) 
(list 4480.135 868.3136) 
(list 4480.135 868.3239) 
(list 4480.135 868.3342) 
(list 4480.135 868.3444) 
(list 4480.135 868.3547) 
(list 4480.135 868.365) 
(list 4480.135 868.3753) 
(list 4480.135 868.3856) 
(list 4480.135 868.3958) 
(list 4480.135 868.4061) 
(list 4480.135 868.4164) 
(list 4480.135 868.4267) 
(list 4480.135 868.4369) 
(list 4480.135 868.4472) 
(list 4480.135 868.4575) 
(list 4480.135 868.4678) 
(list 4480.135 868.4781) 
(list 4480.135 868.4883) 
(list 4480.135 868.4986) 
(list 4480.135 868.5089) 
(list 4480.135 868.5192) 
(list 4480.135 868.5294) 
(list 4480.135 868.5397) 
(list 4480.135 868.55) 
(list 4480 868.55)))
(apply 'command (append '("pline") coords '("c")))
(setq tap14 (ssadd (entlast) tap14))
(command "_mirror" (entlast) "" "4480,900" "4480,901" "No")
(setq tap14 (ssadd (entlast) tap14))
(setq coords (list 
(list 4480.4658 868.18) 
(list 4480.4557 868.18) 
(list 4480.4554 868.1903) 
(list 4480.454 868.2006) 
(list 4480.4516 868.2108) 
(list 4480.4482 868.2211) 
(list 4480.4438 868.2314) 
(list 4480.4387 868.2417) 
(list 4480.4329 868.2519) 
(list 4480.4266 868.2622) 
(list 4480.4201 868.2725) 
(list 4480.4135 868.2828) 
(list 4480.407 868.2931) 
(list 4480.4008 868.3033) 
(list 4480.3951 868.3136) 
(list 4480.3901 868.3239) 
(list 4480.386 868.3342) 
(list 4480.3829 868.3444) 
(list 4480.3809 868.3547) 
(list 4480.38 868.365) 
(list 4480.3805 868.3753) 
(list 4480.3821 868.3856) 
(list 4480.3849 868.3958) 
(list 4480.3889 868.4061) 
(list 4480.3938 868.4164) 
(list 4480.3997 868.4267) 
(list 4480.4062 868.4369) 
(list 4480.4133 868.4472) 
(list 4480.4207 868.4575) 
(list 4480.4282 868.4678) 
(list 4480.4355 868.4781) 
(list 4480.4425 868.4883) 
(list 4480.4489 868.4986) 
(list 4480.4544 868.5089) 
(list 4480.4591 868.5192) 
(list 4480.4626 868.5294) 
(list 4480.4649 868.5397) 
(list 4480.4658 868.55) 
(list 4480.4658 868.55)))
(apply 'command (append '("pline") coords '("c")))
(setq tap14 (ssadd (entlast) tap14))
(command "_mirror" (entlast) "" "4480,900" "4480,901" "No")
(setq tap14 (ssadd (entlast) tap14))
(setq coords (list 
(list 4481.135 868.18) 
(list 4480.4658 868.18) 
(list 4480.4658 868.1903) 
(list 4480.4658 868.2006) 
(list 4480.4658 868.2108) 
(list 4480.4658 868.2211) 
(list 4480.4658 868.2314) 
(list 4480.4658 868.2417) 
(list 4480.4658 868.2519) 
(list 4480.4658 868.2622) 
(list 4480.4658 868.2725) 
(list 4480.4658 868.2828) 
(list 4480.4658 868.2931) 
(list 4480.4658 868.3033) 
(list 4480.4658 868.3136) 
(list 4480.4658 868.3239) 
(list 4480.4658 868.3342) 
(list 4480.4658 868.3444) 
(list 4480.4658 868.3547) 
(list 4480.4658 868.365) 
(list 4480.4658 868.3753) 
(list 4480.4658 868.3856) 
(list 4480.4658 868.3958) 
(list 4480.4658 868.4061) 
(list 4480.4658 868.4164) 
(list 4480.4658 868.4267) 
(list 4480.4658 868.4369) 
(list 4480.4658 868.4472) 
(list 4480.4658 868.4575) 
(list 4480.4658 868.4678) 
(list 4480.4658 868.4781) 
(list 4480.4658 868.4883) 
(list 4480.4658 868.4986) 
(list 4480.4658 868.5089) 
(list 4480.4658 868.5192) 
(list 4480.4658 868.5294) 
(list 4480.4658 868.5397) 
(list 4480.4658 868.55) 
(list 4481.135 868.55)))
(apply 'command (append '("pline") coords '("c")))
(setq tap14 (ssadd (entlast) tap14))
(command "_mirror" (entlast) "" "4480,900" "4480,901" "No")
(setq tap14 (ssadd (entlast) tap14))
(setq coords (list 
(list 4480 868.55) 
(list 4480.135 868.55) 
(list 4480.135 868.5603) 
(list 4480.135 868.5706) 
(list 4480.135 868.5808) 
(list 4480.135 868.5911) 
(list 4480.135 868.6014) 
(list 4480.135 868.6117) 
(list 4480.135 868.6219) 
(list 4480.135 868.6322) 
(list 4480.135 868.6425) 
(list 4480.135 868.6528) 
(list 4480.135 868.6631) 
(list 4480.135 868.6733) 
(list 4480.135 868.6836) 
(list 4480.135 868.6939) 
(list 4480.135 868.7042) 
(list 4480.135 868.7144) 
(list 4480.135 868.7247) 
(list 4480.135 868.735) 
(list 4480.135 868.7453) 
(list 4480.135 868.7556) 
(list 4480.135 868.7658) 
(list 4480.135 868.7761) 
(list 4480.135 868.7864) 
(list 4480.135 868.7967) 
(list 4480.135 868.8069) 
(list 4480.135 868.8172) 
(list 4480.135 868.8275) 
(list 4480.135 868.8378) 
(list 4480.135 868.8481) 
(list 4480.135 868.8583) 
(list 4480.135 868.8686) 
(list 4480.135 868.8789) 
(list 4480.135 868.8892) 
(list 4480.135 868.8994) 
(list 4480.135 868.9097) 
(list 4480.135 868.92) 
(list 4480 868.92)))
(apply 'command (append '("pline") coords '("c")))
(setq tap14 (ssadd (entlast) tap14))
(command "_mirror" (entlast) "" "4480,900" "4480,901" "No")
(setq tap14 (ssadd (entlast) tap14))
(setq coords (list 
(list 4480.476 868.55) 
(list 4480.4658 868.55) 
(list 4480.4654 868.5603) 
(list 4480.4637 868.5706) 
(list 4480.4606 868.5808) 
(list 4480.4562 868.5911) 
(list 4480.4508 868.6014) 
(list 4480.4444 868.6117) 
(list 4480.4372 868.6219) 
(list 4480.4294 868.6322) 
(list 4480.4213 868.6425) 
(list 4480.4131 868.6528) 
(list 4480.4051 868.6631) 
(list 4480.3975 868.6733) 
(list 4480.3905 868.6836) 
(list 4480.3845 868.6939) 
(list 4480.3794 868.7042) 
(list 4480.3757 868.7144) 
(list 4480.3732 868.7247) 
(list 4480.3723 868.735) 
(list 4480.3728 868.7453) 
(list 4480.3749 868.7556) 
(list 4480.3783 868.7658) 
(list 4480.3832 868.7761) 
(list 4480.3893 868.7864) 
(list 4480.3964 868.7967) 
(list 4480.4044 868.8069) 
(list 4480.413 868.8172) 
(list 4480.4219 868.8275) 
(list 4480.4309 868.8378) 
(list 4480.4398 868.8481) 
(list 4480.4482 868.8583) 
(list 4480.4558 868.8686) 
(list 4480.4625 868.8789) 
(list 4480.468 868.8892) 
(list 4480.4722 868.8994) 
(list 4480.4749 868.9097) 
(list 4480.476 868.92) 
(list 4480.476 868.92)))
(apply 'command (append '("pline") coords '("c")))
(setq tap14 (ssadd (entlast) tap14))
(command "_mirror" (entlast) "" "4480,900" "4480,901" "No")
(setq tap14 (ssadd (entlast) tap14))
(setq coords (list 
(list 4481.135 868.55) 
(list 4480.476 868.55) 
(list 4480.476 868.5603) 
(list 4480.476 868.5706) 
(list 4480.476 868.5808) 
(list 4480.476 868.5911) 
(list 4480.476 868.6014) 
(list 4480.476 868.6117) 
(list 4480.476 868.6219) 
(list 4480.476 868.6322) 
(list 4480.476 868.6425) 
(list 4480.476 868.6528) 
(list 4480.476 868.6631) 
(list 4480.476 868.6733) 
(list 4480.476 868.6836) 
(list 4480.476 868.6939) 
(list 4480.476 868.7042) 
(list 4480.476 868.7144) 
(list 4480.476 868.7247) 
(list 4480.476 868.735) 
(list 4480.476 868.7453) 
(list 4480.476 868.7556) 
(list 4480.476 868.7658) 
(list 4480.476 868.7761) 
(list 4480.476 868.7864) 
(list 4480.476 868.7967) 
(list 4480.476 868.8069) 
(list 4480.476 868.8172) 
(list 4480.476 868.8275) 
(list 4480.476 868.8378) 
(list 4480.476 868.8481) 
(list 4480.476 868.8583) 
(list 4480.476 868.8686) 
(list 4480.476 868.8789) 
(list 4480.476 868.8892) 
(list 4480.476 868.8994) 
(list 4480.476 868.9097) 
(list 4480.476 868.92) 
(list 4481.135 868.92)))
(apply 'command (append '("pline") coords '("c")))
(setq tap14 (ssadd (entlast) tap14))
(command "_mirror" (entlast) "" "4480,900" "4480,901" "No")
(setq tap14 (ssadd (entlast) tap14))
(setq coords (list 
(list 4480 868.92) 
(list 4480.135 868.92) 
(list 4480.135 868.9303) 
(list 4480.135 868.9406) 
(list 4480.135 868.9508) 
(list 4480.135 868.9611) 
(list 4480.135 868.9714) 
(list 4480.135 868.9817) 
(list 4480.135 868.9919) 
(list 4480.135 869.0022) 
(list 4480.135 869.0125) 
(list 4480.135 869.0228) 
(list 4480.135 869.0331) 
(list 4480.135 869.0433) 
(list 4480.135 869.0536) 
(list 4480.135 869.0639) 
(list 4480.135 869.0742) 
(list 4480.135 869.0844) 
(list 4480.135 869.0947) 
(list 4480.135 869.105) 
(list 4480.135 869.1153) 
(list 4480.135 869.1256) 
(list 4480.135 869.1358) 
(list 4480.135 869.1461) 
(list 4480.135 869.1564) 
(list 4480.135 869.1667) 
(list 4480.135 869.1769) 
(list 4480.135 869.1872) 
(list 4480.135 869.1975) 
(list 4480.135 869.2078) 
(list 4480.135 869.2181) 
(list 4480.135 869.2283) 
(list 4480.135 869.2386) 
(list 4480.135 869.2489) 
(list 4480.135 869.2592) 
(list 4480.135 869.2694) 
(list 4480.135 869.2797) 
(list 4480.135 869.29) 
(list 4480 869.29)))
(apply 'command (append '("pline") coords '("c")))
(setq tap14 (ssadd (entlast) tap14))
(command "_mirror" (entlast) "" "4480,900" "4480,901" "No")
(setq tap14 (ssadd (entlast) tap14))
(setq coords (list 
(list 4480.4862 868.92) 
(list 4480.476 868.92) 
(list 4480.4755 868.9303) 
(list 4480.4733 868.9406) 
(list 4480.4695 868.9508) 
(list 4480.4643 868.9611) 
(list 4480.4577 868.9714) 
(list 4480.45 868.9817) 
(list 4480.4414 868.9919) 
(list 4480.4322 869.0022) 
(list 4480.4225 869.0125) 
(list 4480.4128 869.0228) 
(list 4480.4032 869.0331) 
(list 4480.3942 869.0433) 
(list 4480.386 869.0536) 
(list 4480.3788 869.0639) 
(list 4480.3729 869.0742) 
(list 4480.3684 869.0844) 
(list 4480.3656 869.0947) 
(list 4480.3645 869.105) 
(list 4480.3652 869.1153) 
(list 4480.3676 869.1256) 
(list 4480.3718 869.1358) 
(list 4480.3775 869.1461) 
(list 4480.3847 869.1564) 
(list 4480.3931 869.1667) 
(list 4480.4025 869.1769) 
(list 4480.4126 869.1872) 
(list 4480.4231 869.1975) 
(list 4480.4337 869.2078) 
(list 4480.444 869.2181) 
(list 4480.4538 869.2283) 
(list 4480.4628 869.2386) 
(list 4480.4706 869.2489) 
(list 4480.477 869.2592) 
(list 4480.4818 869.2694) 
(list 4480.4849 869.2797) 
(list 4480.4862 869.29) 
(list 4480.4862 869.29)))
(apply 'command (append '("pline") coords '("c")))
(setq tap14 (ssadd (entlast) tap14))
(command "_mirror" (entlast) "" "4480,900" "4480,901" "No")
(setq tap14 (ssadd (entlast) tap14))
(setq coords (list 
(list 4481.135 868.92) 
(list 4480.4862 868.92) 
(list 4480.4862 868.9303) 
(list 4480.4862 868.9406) 
(list 4480.4862 868.9508) 
(list 4480.4862 868.9611) 
(list 4480.4862 868.9714) 
(list 4480.4862 868.9817) 
(list 4480.4862 868.9919) 
(list 4480.4862 869.0022) 
(list 4480.4862 869.0125) 
(list 4480.4862 869.0228) 
(list 4480.4862 869.0331) 
(list 4480.4862 869.0433) 
(list 4480.4862 869.0536) 
(list 4480.4862 869.0639) 
(list 4480.4862 869.0742) 
(list 4480.4862 869.0844) 
(list 4480.4862 869.0947) 
(list 4480.4862 869.105) 
(list 4480.4862 869.1153) 
(list 4480.4862 869.1256) 
(list 4480.4862 869.1358) 
(list 4480.4862 869.1461) 
(list 4480.4862 869.1564) 
(list 4480.4862 869.1667) 
(list 4480.4862 869.1769) 
(list 4480.4862 869.1872) 
(list 4480.4862 869.1975) 
(list 4480.4862 869.2078) 
(list 4480.4862 869.2181) 
(list 4480.4862 869.2283) 
(list 4480.4862 869.2386) 
(list 4480.4862 869.2489) 
(list 4480.4862 869.2592) 
(list 4480.4862 869.2694) 
(list 4480.4862 869.2797) 
(list 4480.4862 869.29) 
(list 4481.135 869.29)))
(apply 'command (append '("pline") coords '("c")))
(setq tap14 (ssadd (entlast) tap14))
(command "_mirror" (entlast) "" "4480,900" "4480,901" "No")
(setq tap14 (ssadd (entlast) tap14))
(setq coords (list 
(list 4480 869.29) 
(list 4480.135 869.29) 
(list 4480.135 869.3003) 
(list 4480.135 869.3106) 
(list 4480.135 869.3208) 
(list 4480.135 869.3311) 
(list 4480.135 869.3414) 
(list 4480.135 869.3517) 
(list 4480.135 869.3619) 
(list 4480.135 869.3722) 
(list 4480.135 869.3825) 
(list 4480.135 869.3928) 
(list 4480.135 869.4031) 
(list 4480.135 869.4133) 
(list 4480.135 869.4236) 
(list 4480.135 869.4339) 
(list 4480.135 869.4442) 
(list 4480.135 869.4544) 
(list 4480.135 869.4647) 
(list 4480.135 869.475) 
(list 4480.135 869.4853) 
(list 4480.135 869.4956) 
(list 4480.135 869.5058) 
(list 4480.135 869.5161) 
(list 4480.135 869.5264) 
(list 4480.135 869.5367) 
(list 4480.135 869.5469) 
(list 4480.135 869.5572) 
(list 4480.135 869.5675) 
(list 4480.135 869.5778) 
(list 4480.135 869.5881) 
(list 4480.135 869.5983) 
(list 4480.135 869.6086) 
(list 4480.135 869.6189) 
(list 4480.135 869.6292) 
(list 4480.135 869.6394) 
(list 4480.135 869.6497) 
(list 4480.135 869.66) 
(list 4480 869.66)))
(apply 'command (append '("pline") coords '("c")))
(setq tap14 (ssadd (entlast) tap14))
(command "_mirror" (entlast) "" "4480,900" "4480,901" "No")
(setq tap14 (ssadd (entlast) tap14))
(setq coords (list 
(list 4480.4963 869.29) 
(list 4480.4862 869.29) 
(list 4480.4855 869.3003) 
(list 4480.4829 869.3106) 
(list 4480.4785 869.3208) 
(list 4480.4724 869.3311) 
(list 4480.4647 869.3414) 
(list 4480.4557 869.3517) 
(list 4480.4457 869.3619) 
(list 4480.4349 869.3722) 
(list 4480.4237 869.3825) 
(list 4480.4124 869.3928) 
(list 4480.4014 869.4031) 
(list 4480.3909 869.4133) 
(list 4480.3814 869.4236) 
(list 4480.3731 869.4339) 
(list 4480.3663 869.4442) 
(list 4480.3612 869.4544) 
(list 4480.358 869.4647) 
(list 4480.3567 869.475) 
(list 4480.3576 869.4853) 
(list 4480.3604 869.4956) 
(list 4480.3652 869.5058) 
(list 4480.3719 869.5161) 
(list 4480.3801 869.5264) 
(list 4480.3898 869.5367) 
(list 4480.4006 869.5469) 
(list 4480.4122 869.5572) 
(list 4480.4243 869.5675) 
(list 4480.4364 869.5778) 
(list 4480.4483 869.5881) 
(list 4480.4595 869.5983) 
(list 4480.4697 869.6086) 
(list 4480.4787 869.6189) 
(list 4480.486 869.6292) 
(list 4480.4915 869.6394) 
(list 4480.495 869.6497) 
(list 4480.4963 869.66) 
(list 4480.4963 869.66)))
(apply 'command (append '("pline") coords '("c")))
(setq tap14 (ssadd (entlast) tap14))
(command "_mirror" (entlast) "" "4480,900" "4480,901" "No")
(setq tap14 (ssadd (entlast) tap14))
(setq coords (list 
(list 4481.135 869.29) 
(list 4480.4963 869.29) 
(list 4480.4963 869.3003) 
(list 4480.4963 869.3106) 
(list 4480.4963 869.3208) 
(list 4480.4963 869.3311) 
(list 4480.4963 869.3414) 
(list 4480.4963 869.3517) 
(list 4480.4963 869.3619) 
(list 4480.4963 869.3722) 
(list 4480.4963 869.3825) 
(list 4480.4963 869.3928) 
(list 4480.4963 869.4031) 
(list 4480.4963 869.4133) 
(list 4480.4963 869.4236) 
(list 4480.4963 869.4339) 
(list 4480.4963 869.4442) 
(list 4480.4963 869.4544) 
(list 4480.4963 869.4647) 
(list 4480.4963 869.475) 
(list 4480.4963 869.4853) 
(list 4480.4963 869.4956) 
(list 4480.4963 869.5058) 
(list 4480.4963 869.5161) 
(list 4480.4963 869.5264) 
(list 4480.4963 869.5367) 
(list 4480.4963 869.5469) 
(list 4480.4963 869.5572) 
(list 4480.4963 869.5675) 
(list 4480.4963 869.5778) 
(list 4480.4963 869.5881) 
(list 4480.4963 869.5983) 
(list 4480.4963 869.6086) 
(list 4480.4963 869.6189) 
(list 4480.4963 869.6292) 
(list 4480.4963 869.6394) 
(list 4480.4963 869.6497) 
(list 4480.4963 869.66) 
(list 4481.135 869.66)))
(apply 'command (append '("pline") coords '("c")))
(setq tap14 (ssadd (entlast) tap14))
(command "_mirror" (entlast) "" "4480,900" "4480,901" "No")
(setq tap14 (ssadd (entlast) tap14))
(setq coords (list 
(list 4480 869.66) 
(list 4480.135 869.66) 
(list 4480.135 869.6703) 
(list 4480.135 869.6806) 
(list 4480.135 869.6908) 
(list 4480.135 869.7011) 
(list 4480.135 869.7114) 
(list 4480.135 869.7217) 
(list 4480.135 869.7319) 
(list 4480.135 869.7422) 
(list 4480.135 869.7525) 
(list 4480.135 869.7628) 
(list 4480.135 869.7731) 
(list 4480.135 869.7833) 
(list 4480.135 869.7936) 
(list 4480.135 869.8039) 
(list 4480.135 869.8142) 
(list 4480.135 869.8244) 
(list 4480.135 869.8347) 
(list 4480.135 869.845) 
(list 4480.135 869.8553) 
(list 4480.135 869.8656) 
(list 4480.135 869.8758) 
(list 4480.135 869.8861) 
(list 4480.135 869.8964) 
(list 4480.135 869.9067) 
(list 4480.135 869.9169) 
(list 4480.135 869.9272) 
(list 4480.135 869.9375) 
(list 4480.135 869.9478) 
(list 4480.135 869.9581) 
(list 4480.135 869.9683) 
(list 4480.135 869.9786) 
(list 4480.135 869.9889) 
(list 4480.135 869.9992) 
(list 4480.135 870.0094) 
(list 4480.135 870.0197) 
(list 4480.135 870.03) 
(list 4480 870.03)))
(apply 'command (append '("pline") coords '("c")))
(setq tap14 (ssadd (entlast) tap14))
(command "_mirror" (entlast) "" "4480,900" "4480,901" "No")
(setq tap14 (ssadd (entlast) tap14))
(setq coords (list 
(list 4480.5065 869.66) 
(list 4480.4963 869.66) 
(list 4480.4955 869.6703) 
(list 4480.4925 869.6806) 
(list 4480.4875 869.6908) 
(list 4480.4804 869.7011) 
(list 4480.4717 869.7114) 
(list 4480.4614 869.7217) 
(list 4480.45 869.7319) 
(list 4480.4377 869.7422) 
(list 4480.4249 869.7525) 
(list 4480.412 869.7628) 
(list 4480.3995 869.7731) 
(list 4480.3876 869.7833) 
(list 4480.3768 869.7936) 
(list 4480.3674 869.8039) 
(list 4480.3597 869.8142) 
(list 4480.354 869.8244) 
(list 4480.3504 869.8347) 
(list 4480.349 869.845) 
(list 4480.3499 869.8553) 
(list 4480.3532 869.8656) 
(list 4480.3586 869.8758) 
(list 4480.3662 869.8861) 
(list 4480.3756 869.8964) 
(list 4480.3865 869.9067) 
(list 4480.3988 869.9169) 
(list 4480.4119 869.9272) 
(list 4480.4255 869.9375) 
(list 4480.4392 869.9478) 
(list 4480.4526 869.9581) 
(list 4480.4652 869.9683) 
(list 4480.4767 869.9786) 
(list 4480.4867 869.9889) 
(list 4480.4949 869.9992) 
(list 4480.5011 870.0094) 
(list 4480.505 870.0197) 
(list 4480.5065 870.03) 
(list 4480.5065 870.03)))
(apply 'command (append '("pline") coords '("c")))
(setq tap14 (ssadd (entlast) tap14))
(command "_mirror" (entlast) "" "4480,900" "4480,901" "No")
(setq tap14 (ssadd (entlast) tap14))
(setq coords (list 
(list 4481.135 869.66) 
(list 4480.5065 869.66) 
(list 4480.5065 869.6703) 
(list 4480.5065 869.6806) 
(list 4480.5065 869.6908) 
(list 4480.5065 869.7011) 
(list 4480.5065 869.7114) 
(list 4480.5065 869.7217) 
(list 4480.5065 869.7319) 
(list 4480.5065 869.7422) 
(list 4480.5065 869.7525) 
(list 4480.5065 869.7628) 
(list 4480.5065 869.7731) 
(list 4480.5065 869.7833) 
(list 4480.5065 869.7936) 
(list 4480.5065 869.8039) 
(list 4480.5065 869.8142) 
(list 4480.5065 869.8244) 
(list 4480.5065 869.8347) 
(list 4480.5065 869.845) 
(list 4480.5065 869.8553) 
(list 4480.5065 869.8656) 
(list 4480.5065 869.8758) 
(list 4480.5065 869.8861) 
(list 4480.5065 869.8964) 
(list 4480.5065 869.9067) 
(list 4480.5065 869.9169) 
(list 4480.5065 869.9272) 
(list 4480.5065 869.9375) 
(list 4480.5065 869.9478) 
(list 4480.5065 869.9581) 
(list 4480.5065 869.9683) 
(list 4480.5065 869.9786) 
(list 4480.5065 869.9889) 
(list 4480.5065 869.9992) 
(list 4480.5065 870.0094) 
(list 4480.5065 870.0197) 
(list 4480.5065 870.03) 
(list 4481.135 870.03)))
(apply 'command (append '("pline") coords '("c")))
(setq tap14 (ssadd (entlast) tap14))
(command "_mirror" (entlast) "" "4480,900" "4480,901" "No")
(setq tap14 (ssadd (entlast) tap14))
(setq coords (list 
(list 4480 870.03) 
(list 4480.135 870.03) 
(list 4480.135 870.0403) 
(list 4480.135 870.0506) 
(list 4480.135 870.0608) 
(list 4480.135 870.0711) 
(list 4480.135 870.0814) 
(list 4480.135 870.0917) 
(list 4480.135 870.1019) 
(list 4480.135 870.1122) 
(list 4480.135 870.1225) 
(list 4480.135 870.1328) 
(list 4480.135 870.1431) 
(list 4480.135 870.1533) 
(list 4480.135 870.1636) 
(list 4480.135 870.1739) 
(list 4480.135 870.1842) 
(list 4480.135 870.1944) 
(list 4480.135 870.2047) 
(list 4480.135 870.215) 
(list 4480.135 870.2253) 
(list 4480.135 870.2356) 
(list 4480.135 870.2458) 
(list 4480.135 870.2561) 
(list 4480.135 870.2664) 
(list 4480.135 870.2767) 
(list 4480.135 870.2869) 
(list 4480.135 870.2972) 
(list 4480.135 870.3075) 
(list 4480.135 870.3178) 
(list 4480.135 870.3281) 
(list 4480.135 870.3383) 
(list 4480.135 870.3486) 
(list 4480.135 870.3589) 
(list 4480.135 870.3692) 
(list 4480.135 870.3794) 
(list 4480.135 870.3897) 
(list 4480.135 870.4) 
(list 4480 870.4)))
(apply 'command (append '("pline") coords '("c")))
(setq tap14 (ssadd (entlast) tap14))
(command "_mirror" (entlast) "" "4480,900" "4480,901" "No")
(setq tap14 (ssadd (entlast) tap14))
(setq coords (list 
(list 4480.5167 870.03) 
(list 4480.5065 870.03) 
(list 4480.5056 870.0403) 
(list 4480.5022 870.0506) 
(list 4480.4964 870.0608) 
(list 4480.4885 870.0711) 
(list 4480.4786 870.0814) 
(list 4480.4671 870.0917) 
(list 4480.4542 870.1019) 
(list 4480.4404 870.1122) 
(list 4480.4261 870.1225) 
(list 4480.4117 870.1328) 
(list 4480.3976 870.1431) 
(list 4480.3844 870.1533) 
(list 4480.3723 870.1636) 
(list 4480.3618 870.1739) 
(list 4480.3532 870.1842) 
(list 4480.3468 870.1944) 
(list 4480.3427 870.2047) 
(list 4480.3412 870.215) 
(list 4480.3423 870.2253) 
(list 4480.346 870.2356) 
(list 4480.3521 870.2458) 
(list 4480.3605 870.2561) 
(list 4480.371 870.2664) 
(list 4480.3833 870.2767) 
(list 4480.3969 870.2869) 
(list 4480.4115 870.2972) 
(list 4480.4267 870.3075) 
(list 4480.442 870.3178) 
(list 4480.4568 870.3281) 
(list 4480.4709 870.3383) 
(list 4480.4837 870.3486) 
(list 4480.4948 870.3589) 
(list 4480.5039 870.3692) 
(list 4480.5107 870.3794) 
(list 4480.515 870.3897) 
(list 4480.5167 870.4) 
(list 4480.5167 870.4)))
(apply 'command (append '("pline") coords '("c")))
(setq tap14 (ssadd (entlast) tap14))
(command "_mirror" (entlast) "" "4480,900" "4480,901" "No")
(setq tap14 (ssadd (entlast) tap14))
(setq coords (list 
(list 4481.135 870.03) 
(list 4480.5167 870.03) 
(list 4480.5167 870.0403) 
(list 4480.5167 870.0506) 
(list 4480.5167 870.0608) 
(list 4480.5167 870.0711) 
(list 4480.5167 870.0814) 
(list 4480.5167 870.0917) 
(list 4480.5167 870.1019) 
(list 4480.5167 870.1122) 
(list 4480.5167 870.1225) 
(list 4480.5167 870.1328) 
(list 4480.5167 870.1431) 
(list 4480.5167 870.1533) 
(list 4480.5167 870.1636) 
(list 4480.5167 870.1739) 
(list 4480.5167 870.1842) 
(list 4480.5167 870.1944) 
(list 4480.5167 870.2047) 
(list 4480.5167 870.215) 
(list 4480.5167 870.2253) 
(list 4480.5167 870.2356) 
(list 4480.5167 870.2458) 
(list 4480.5167 870.2561) 
(list 4480.5167 870.2664) 
(list 4480.5167 870.2767) 
(list 4480.5167 870.2869) 
(list 4480.5167 870.2972) 
(list 4480.5167 870.3075) 
(list 4480.5167 870.3178) 
(list 4480.5167 870.3281) 
(list 4480.5167 870.3383) 
(list 4480.5167 870.3486) 
(list 4480.5167 870.3589) 
(list 4480.5167 870.3692) 
(list 4480.5167 870.3794) 
(list 4480.5167 870.3897) 
(list 4480.5167 870.4) 
(list 4481.135 870.4)))
(apply 'command (append '("pline") coords '("c")))
(setq tap14 (ssadd (entlast) tap14))
(command "_mirror" (entlast) "" "4480,900" "4480,901" "No")
(setq tap14 (ssadd (entlast) tap14))
(setq coords (list 
(list 4480 870.4) 
(list 4480.135 870.4) 
(list 4480.135 870.4103) 
(list 4480.135 870.4206) 
(list 4480.135 870.4308) 
(list 4480.135 870.4411) 
(list 4480.135 870.4514) 
(list 4480.135 870.4617) 
(list 4480.135 870.4719) 
(list 4480.135 870.4822) 
(list 4480.135 870.4925) 
(list 4480.135 870.5028) 
(list 4480.135 870.5131) 
(list 4480.135 870.5233) 
(list 4480.135 870.5336) 
(list 4480.135 870.5439) 
(list 4480.135 870.5542) 
(list 4480.135 870.5644) 
(list 4480.135 870.5747) 
(list 4480.135 870.585) 
(list 4480.135 870.5953) 
(list 4480.135 870.6056) 
(list 4480.135 870.6158) 
(list 4480.135 870.6261) 
(list 4480.135 870.6364) 
(list 4480.135 870.6467) 
(list 4480.135 870.6569) 
(list 4480.135 870.6672) 
(list 4480.135 870.6775) 
(list 4480.135 870.6878) 
(list 4480.135 870.6981) 
(list 4480.135 870.7083) 
(list 4480.135 870.7186) 
(list 4480.135 870.7289) 
(list 4480.135 870.7392) 
(list 4480.135 870.7494) 
(list 4480.135 870.7597) 
(list 4480.135 870.77) 
(list 4480 870.77)))
(apply 'command (append '("pline") coords '("c")))
(setq tap14 (ssadd (entlast) tap14))
(command "_mirror" (entlast) "" "4480,900" "4480,901" "No")
(setq tap14 (ssadd (entlast) tap14))
(setq coords (list 
(list 4480.5268 870.4) 
(list 4480.5167 870.4) 
(list 4480.5156 870.4103) 
(list 4480.5118 870.4206) 
(list 4480.5054 870.4308) 
(list 4480.4966 870.4411) 
(list 4480.4856 870.4514) 
(list 4480.4728 870.4617) 
(list 4480.4585 870.4719) 
(list 4480.4432 870.4822) 
(list 4480.4273 870.4925) 
(list 4480.4113 870.5028) 
(list 4480.3958 870.5131) 
(list 4480.3811 870.5233) 
(list 4480.3677 870.5336) 
(list 4480.3561 870.5439) 
(list 4480.3466 870.5542) 
(list 4480.3395 870.5644) 
(list 4480.3351 870.5747) 
(list 4480.3335 870.585) 
(list 4480.3347 870.5953) 
(list 4480.3387 870.6056) 
(list 4480.3455 870.6158) 
(list 4480.3548 870.6261) 
(list 4480.3664 870.6364) 
(list 4480.38 870.6467) 
(list 4480.395 870.6569) 
(list 4480.4112 870.6672) 
(list 4480.4279 870.6775) 
(list 4480.4447 870.6878) 
(list 4480.4611 870.6981) 
(list 4480.4766 870.7083) 
(list 4480.4906 870.7186) 
(list 4480.5029 870.7289) 
(list 4480.5129 870.7392) 
(list 4480.5204 870.7494) 
(list 4480.5251 870.7597) 
(list 4480.5268 870.77) 
(list 4480.5268 870.77)))
(apply 'command (append '("pline") coords '("c")))
(setq tap14 (ssadd (entlast) tap14))
(command "_mirror" (entlast) "" "4480,900" "4480,901" "No")
(setq tap14 (ssadd (entlast) tap14))
(setq coords (list 
(list 4481.135 870.4) 
(list 4480.5268 870.4) 
(list 4480.5268 870.4103) 
(list 4480.5268 870.4206) 
(list 4480.5268 870.4308) 
(list 4480.5268 870.4411) 
(list 4480.5268 870.4514) 
(list 4480.5268 870.4617) 
(list 4480.5268 870.4719) 
(list 4480.5268 870.4822) 
(list 4480.5268 870.4925) 
(list 4480.5268 870.5028) 
(list 4480.5268 870.5131) 
(list 4480.5268 870.5233) 
(list 4480.5268 870.5336) 
(list 4480.5268 870.5439) 
(list 4480.5268 870.5542) 
(list 4480.5268 870.5644) 
(list 4480.5268 870.5747) 
(list 4480.5268 870.585) 
(list 4480.5268 870.5953) 
(list 4480.5268 870.6056) 
(list 4480.5268 870.6158) 
(list 4480.5268 870.6261) 
(list 4480.5268 870.6364) 
(list 4480.5268 870.6467) 
(list 4480.5268 870.6569) 
(list 4480.5268 870.6672) 
(list 4480.5268 870.6775) 
(list 4480.5268 870.6878) 
(list 4480.5268 870.6981) 
(list 4480.5268 870.7083) 
(list 4480.5268 870.7186) 
(list 4480.5268 870.7289) 
(list 4480.5268 870.7392) 
(list 4480.5268 870.7494) 
(list 4480.5268 870.7597) 
(list 4480.5268 870.77) 
(list 4481.135 870.77)))
(apply 'command (append '("pline") coords '("c")))
(setq tap14 (ssadd (entlast) tap14))
(command "_mirror" (entlast) "" "4480,900" "4480,901" "No")
(setq tap14 (ssadd (entlast) tap14))
(setq coords (list 
(list 4480 870.77) 
(list 4480.135 870.77) 
(list 4480.135 870.7803) 
(list 4480.135 870.7906) 
(list 4480.135 870.8008) 
(list 4480.135 870.8111) 
(list 4480.135 870.8214) 
(list 4480.135 870.8317) 
(list 4480.135 870.8419) 
(list 4480.135 870.8522) 
(list 4480.135 870.8625) 
(list 4480.135 870.8728) 
(list 4480.135 870.8831) 
(list 4480.135 870.8933) 
(list 4480.135 870.9036) 
(list 4480.135 870.9139) 
(list 4480.135 870.9242) 
(list 4480.135 870.9344) 
(list 4480.135 870.9447) 
(list 4480.135 870.955) 
(list 4480.135 870.9653) 
(list 4480.135 870.9756) 
(list 4480.135 870.9858) 
(list 4480.135 870.9961) 
(list 4480.135 871.0064) 
(list 4480.135 871.0167) 
(list 4480.135 871.0269) 
(list 4480.135 871.0372) 
(list 4480.135 871.0475) 
(list 4480.135 871.0578) 
(list 4480.135 871.0681) 
(list 4480.135 871.0783) 
(list 4480.135 871.0886) 
(list 4480.135 871.0989) 
(list 4480.135 871.1092) 
(list 4480.135 871.1194) 
(list 4480.135 871.1297) 
(list 4480.135 871.14) 
(list 4480 871.14)))
(apply 'command (append '("pline") coords '("c")))
(setq tap14 (ssadd (entlast) tap14))
(command "_mirror" (entlast) "" "4480,900" "4480,901" "No")
(setq tap14 (ssadd (entlast) tap14))
(setq coords (list 
(list 4480.537 870.77) 
(list 4480.5268 870.77) 
(list 4480.5256 870.7803) 
(list 4480.5214 870.7906) 
(list 4480.5144 870.8008) 
(list 4480.5047 870.8111) 
(list 4480.4926 870.8214) 
(list 4480.4785 870.8317) 
(list 4480.4628 870.8419) 
(list 4480.4459 870.8522) 
(list 4480.4285 870.8625) 
(list 4480.411 870.8728) 
(list 4480.3939 870.8831) 
(list 4480.3778 870.8933) 
(list 4480.3632 870.9036) 
(list 4480.3504 870.9139) 
(list 4480.34 870.9242) 
(list 4480.3323 870.9344) 
(list 4480.3275 870.9447) 
(list 4480.3257 870.955) 
(list 4480.327 870.9653) 
(list 4480.3315 870.9756) 
(list 4480.339 870.9858) 
(list 4480.3492 870.9961) 
(list 4480.3619 871.0064) 
(list 4480.3767 871.0167) 
(list 4480.3932 871.0269) 
(list 4480.4108 871.0372) 
(list 4480.4291 871.0475) 
(list 4480.4475 871.0578) 
(list 4480.4654 871.0681) 
(list 4480.4823 871.0783) 
(list 4480.4976 871.0886) 
(list 4480.5109 871.0989) 
(list 4480.5218 871.1092) 
(list 4480.53 871.1194) 
(list 4480.5351 871.1297) 
(list 4480.537 871.14) 
(list 4480.537 871.14)))
(apply 'command (append '("pline") coords '("c")))
(setq tap14 (ssadd (entlast) tap14))
(command "_mirror" (entlast) "" "4480,900" "4480,901" "No")
(setq tap14 (ssadd (entlast) tap14))
(setq coords (list 
(list 4481.135 870.77) 
(list 4480.537 870.77) 
(list 4480.537 870.7803) 
(list 4480.537 870.7906) 
(list 4480.537 870.8008) 
(list 4480.537 870.8111) 
(list 4480.537 870.8214) 
(list 4480.537 870.8317) 
(list 4480.537 870.8419) 
(list 4480.537 870.8522) 
(list 4480.537 870.8625) 
(list 4480.537 870.8728) 
(list 4480.537 870.8831) 
(list 4480.537 870.8933) 
(list 4480.537 870.9036) 
(list 4480.537 870.9139) 
(list 4480.537 870.9242) 
(list 4480.537 870.9344) 
(list 4480.537 870.9447) 
(list 4480.537 870.955) 
(list 4480.537 870.9653) 
(list 4480.537 870.9756) 
(list 4480.537 870.9858) 
(list 4480.537 870.9961) 
(list 4480.537 871.0064) 
(list 4480.537 871.0167) 
(list 4480.537 871.0269) 
(list 4480.537 871.0372) 
(list 4480.537 871.0475) 
(list 4480.537 871.0578) 
(list 4480.537 871.0681) 
(list 4480.537 871.0783) 
(list 4480.537 871.0886) 
(list 4480.537 871.0989) 
(list 4480.537 871.1092) 
(list 4480.537 871.1194) 
(list 4480.537 871.1297) 
(list 4480.537 871.14) 
(list 4481.135 871.14)))
(apply 'command (append '("pline") coords '("c")))
(setq tap14 (ssadd (entlast) tap14))
(command "_mirror" (entlast) "" "4480,900" "4480,901" "No")
(setq tap14 (ssadd (entlast) tap14))
(setq coords (list 
(list 4480 871.14) 
(list 4480.135 871.14) 
(list 4480.135 871.1503) 
(list 4480.135 871.1606) 
(list 4480.135 871.1708) 
(list 4480.135 871.1811) 
(list 4480.135 871.1914) 
(list 4480.135 871.2017) 
(list 4480.135 871.2119) 
(list 4480.135 871.2222) 
(list 4480.135 871.2325) 
(list 4480.135 871.2428) 
(list 4480.135 871.2531) 
(list 4480.135 871.2633) 
(list 4480.135 871.2736) 
(list 4480.135 871.2839) 
(list 4480.135 871.2942) 
(list 4480.135 871.3044) 
(list 4480.135 871.3147) 
(list 4480.135 871.325) 
(list 4480.135 871.3353) 
(list 4480.135 871.3456) 
(list 4480.135 871.3558) 
(list 4480.135 871.3661) 
(list 4480.135 871.3764) 
(list 4480.135 871.3867) 
(list 4480.135 871.3969) 
(list 4480.135 871.4072) 
(list 4480.135 871.4175) 
(list 4480.135 871.4278) 
(list 4480.135 871.4381) 
(list 4480.135 871.4483) 
(list 4480.135 871.4586) 
(list 4480.135 871.4689) 
(list 4480.135 871.4792) 
(list 4480.135 871.4894) 
(list 4480.135 871.4997) 
(list 4480.135 871.51) 
(list 4480 871.51)))
(apply 'command (append '("pline") coords '("c")))
(setq tap14 (ssadd (entlast) tap14))
(command "_mirror" (entlast) "" "4480,900" "4480,901" "No")
(setq tap14 (ssadd (entlast) tap14))
(setq coords (list 
(list 4480.5472 871.14) 
(list 4480.537 871.14) 
(list 4480.5356 871.1503) 
(list 4480.531 871.1606) 
(list 4480.5233 871.1708) 
(list 4480.5127 871.1811) 
(list 4480.4995 871.1914) 
(list 4480.4841 871.2017) 
(list 4480.467 871.2119) 
(list 4480.4487 871.2222) 
(list 4480.4297 871.2325) 
(list 4480.4106 871.2428) 
(list 4480.392 871.2531) 
(list 4480.3745 871.2633) 
(list 4480.3586 871.2736) 
(list 4480.3448 871.2839) 
(list 4480.3335 871.2942) 
(list 4480.3251 871.3044) 
(list 4480.3198 871.3147) 
(list 4480.3179 871.325) 
(list 4480.3194 871.3353) 
(list 4480.3243 871.3456) 
(list 4480.3324 871.3558) 
(list 4480.3435 871.3661) 
(list 4480.3573 871.3764) 
(list 4480.3734 871.3867) 
(list 4480.3913 871.3969) 
(list 4480.4105 871.4072) 
(list 4480.4303 871.4175) 
(list 4480.4502 871.4278) 
(list 4480.4696 871.4381) 
(list 4480.4879 871.4483) 
(list 4480.5046 871.4586) 
(list 4480.519 871.4689) 
(list 4480.5308 871.4792) 
(list 4480.5396 871.4894) 
(list 4480.5451 871.4997) 
(list 4480.5472 871.51) 
(list 4480.5472 871.51)))
(apply 'command (append '("pline") coords '("c")))
(setq tap14 (ssadd (entlast) tap14))
(command "_mirror" (entlast) "" "4480,900" "4480,901" "No")
(setq tap14 (ssadd (entlast) tap14))
(setq coords (list 
(list 4481.135 871.14) 
(list 4480.5472 871.14) 
(list 4480.5472 871.1503) 
(list 4480.5472 871.1606) 
(list 4480.5472 871.1708) 
(list 4480.5472 871.1811) 
(list 4480.5472 871.1914) 
(list 4480.5472 871.2017) 
(list 4480.5472 871.2119) 
(list 4480.5472 871.2222) 
(list 4480.5472 871.2325) 
(list 4480.5472 871.2428) 
(list 4480.5472 871.2531) 
(list 4480.5472 871.2633) 
(list 4480.5472 871.2736) 
(list 4480.5472 871.2839) 
(list 4480.5472 871.2942) 
(list 4480.5472 871.3044) 
(list 4480.5472 871.3147) 
(list 4480.5472 871.325) 
(list 4480.5472 871.3353) 
(list 4480.5472 871.3456) 
(list 4480.5472 871.3558) 
(list 4480.5472 871.3661) 
(list 4480.5472 871.3764) 
(list 4480.5472 871.3867) 
(list 4480.5472 871.3969) 
(list 4480.5472 871.4072) 
(list 4480.5472 871.4175) 
(list 4480.5472 871.4278) 
(list 4480.5472 871.4381) 
(list 4480.5472 871.4483) 
(list 4480.5472 871.4586) 
(list 4480.5472 871.4689) 
(list 4480.5472 871.4792) 
(list 4480.5472 871.4894) 
(list 4480.5472 871.4997) 
(list 4480.5472 871.51) 
(list 4481.135 871.51)))
(apply 'command (append '("pline") coords '("c")))
(setq tap14 (ssadd (entlast) tap14))
(command "_mirror" (entlast) "" "4480,900" "4480,901" "No")
(setq tap14 (ssadd (entlast) tap14))
(setq coords (list 
(list 4480 871.51) 
(list 4480.135 871.51) 
(list 4480.135 871.5203) 
(list 4480.135 871.5306) 
(list 4480.135 871.5408) 
(list 4480.135 871.5511) 
(list 4480.135 871.5614) 
(list 4480.135 871.5717) 
(list 4480.135 871.5819) 
(list 4480.135 871.5922) 
(list 4480.135 871.6025) 
(list 4480.135 871.6128) 
(list 4480.135 871.6231) 
(list 4480.135 871.6333) 
(list 4480.135 871.6436) 
(list 4480.135 871.6539) 
(list 4480.135 871.6642) 
(list 4480.135 871.6744) 
(list 4480.135 871.6847) 
(list 4480.135 871.695) 
(list 4480.135 871.7053) 
(list 4480.135 871.7156) 
(list 4480.135 871.7258) 
(list 4480.135 871.7361) 
(list 4480.135 871.7464) 
(list 4480.135 871.7567) 
(list 4480.135 871.7669) 
(list 4480.135 871.7772) 
(list 4480.135 871.7875) 
(list 4480.135 871.7978) 
(list 4480.135 871.8081) 
(list 4480.135 871.8183) 
(list 4480.135 871.8286) 
(list 4480.135 871.8389) 
(list 4480.135 871.8492) 
(list 4480.135 871.8594) 
(list 4480.135 871.8697) 
(list 4480.135 871.88) 
(list 4480 871.88)))
(apply 'command (append '("pline") coords '("c")))
(setq tap14 (ssadd (entlast) tap14))
(command "_mirror" (entlast) "" "4480,900" "4480,901" "No")
(setq tap14 (ssadd (entlast) tap14))
(setq coords (list 
(list 4480.5573 871.51) 
(list 4480.5472 871.51) 
(list 4480.5457 871.5203) 
(list 4480.5407 871.5306) 
(list 4480.5323 871.5408) 
(list 4480.5208 871.5511) 
(list 4480.5065 871.5614) 
(list 4480.4898 871.5717) 
(list 4480.4713 871.5819) 
(list 4480.4515 871.5922) 
(list 4480.4309 871.6025) 
(list 4480.4103 871.6128) 
(list 4480.3902 871.6231) 
(list 4480.3712 871.6333) 
(list 4480.354 871.6436) 
(list 4480.3391 871.6539) 
(list 4480.3269 871.6642) 
(list 4480.3179 871.6744) 
(list 4480.3122 871.6847) 
(list 4480.3102 871.695) 
(list 4480.3118 871.7053) 
(list 4480.317 871.7156) 
(list 4480.3258 871.7258) 
(list 4480.3378 871.7361) 
(list 4480.3528 871.7464) 
(list 4480.3701 871.7567) 
(list 4480.3894 871.7669) 
(list 4480.4101 871.7772) 
(list 4480.4315 871.7875) 
(list 4480.453 871.7978) 
(list 4480.4739 871.8081) 
(list 4480.4936 871.8183) 
(list 4480.5115 871.8286) 
(list 4480.5271 871.8389) 
(list 4480.5398 871.8492) 
(list 4480.5492 871.8594) 
(list 4480.5551 871.8697) 
(list 4480.5573 871.88) 
(list 4480.5573 871.88)))
(apply 'command (append '("pline") coords '("c")))
(setq tap14 (ssadd (entlast) tap14))
(command "_mirror" (entlast) "" "4480,900" "4480,901" "No")
(setq tap14 (ssadd (entlast) tap14))
(setq coords (list 
(list 4481.135 871.51) 
(list 4480.5573 871.51) 
(list 4480.5573 871.5203) 
(list 4480.5573 871.5306) 
(list 4480.5573 871.5408) 
(list 4480.5573 871.5511) 
(list 4480.5573 871.5614) 
(list 4480.5573 871.5717) 
(list 4480.5573 871.5819) 
(list 4480.5573 871.5922) 
(list 4480.5573 871.6025) 
(list 4480.5573 871.6128) 
(list 4480.5573 871.6231) 
(list 4480.5573 871.6333) 
(list 4480.5573 871.6436) 
(list 4480.5573 871.6539) 
(list 4480.5573 871.6642) 
(list 4480.5573 871.6744) 
(list 4480.5573 871.6847) 
(list 4480.5573 871.695) 
(list 4480.5573 871.7053) 
(list 4480.5573 871.7156) 
(list 4480.5573 871.7258) 
(list 4480.5573 871.7361) 
(list 4480.5573 871.7464) 
(list 4480.5573 871.7567) 
(list 4480.5573 871.7669) 
(list 4480.5573 871.7772) 
(list 4480.5573 871.7875) 
(list 4480.5573 871.7978) 
(list 4480.5573 871.8081) 
(list 4480.5573 871.8183) 
(list 4480.5573 871.8286) 
(list 4480.5573 871.8389) 
(list 4480.5573 871.8492) 
(list 4480.5573 871.8594) 
(list 4480.5573 871.8697) 
(list 4480.5573 871.88) 
(list 4481.135 871.88)))
(apply 'command (append '("pline") coords '("c")))
(setq tap14 (ssadd (entlast) tap14))
(command "_mirror" (entlast) "" "4480,900" "4480,901" "No")
(setq tap14 (ssadd (entlast) tap14))
(setq coords (list 
(list 4480 871.88) 
(list 4480.135 871.88) 
(list 4480.135 871.8903) 
(list 4480.135 871.9006) 
(list 4480.135 871.9108) 
(list 4480.135 871.9211) 
(list 4480.135 871.9314) 
(list 4480.135 871.9417) 
(list 4480.135 871.9519) 
(list 4480.135 871.9622) 
(list 4480.135 871.9725) 
(list 4480.135 871.9828) 
(list 4480.135 871.9931) 
(list 4480.135 872.0033) 
(list 4480.135 872.0136) 
(list 4480.135 872.0239) 
(list 4480.135 872.0342) 
(list 4480.135 872.0444) 
(list 4480.135 872.0547) 
(list 4480.135 872.065) 
(list 4480.135 872.0753) 
(list 4480.135 872.0856) 
(list 4480.135 872.0958) 
(list 4480.135 872.1061) 
(list 4480.135 872.1164) 
(list 4480.135 872.1267) 
(list 4480.135 872.1369) 
(list 4480.135 872.1472) 
(list 4480.135 872.1575) 
(list 4480.135 872.1678) 
(list 4480.135 872.1781) 
(list 4480.135 872.1883) 
(list 4480.135 872.1986) 
(list 4480.135 872.2089) 
(list 4480.135 872.2192) 
(list 4480.135 872.2294) 
(list 4480.135 872.2397) 
(list 4480.135 872.25) 
(list 4480 872.25)))
(apply 'command (append '("pline") coords '("c")))
(setq tap14 (ssadd (entlast) tap14))
(command "_mirror" (entlast) "" "4480,900" "4480,901" "No")
(setq tap14 (ssadd (entlast) tap14))
(setq coords (list 
(list 4480.5675 871.88) 
(list 4480.5573 871.88) 
(list 4480.5557 871.8903) 
(list 4480.5503 871.9006) 
(list 4480.5413 871.9108) 
(list 4480.5289 871.9211) 
(list 4480.5135 871.9314) 
(list 4480.4955 871.9417) 
(list 4480.4756 871.9519) 
(list 4480.4542 871.9622) 
(list 4480.4321 871.9725) 
(list 4480.4099 871.9828) 
(list 4480.3883 871.9931) 
(list 4480.3679 872.0033) 
(list 4480.3495 872.0136) 
(list 4480.3334 872.0239) 
(list 4480.3203 872.0342) 
(list 4480.3106 872.0444) 
(list 4480.3046 872.0547) 
(list 4480.3024 872.065) 
(list 4480.3041 872.0753) 
(list 4480.3098 872.0856) 
(list 4480.3193 872.0958) 
(list 4480.3322 872.1061) 
(list 4480.3482 872.1164) 
(list 4480.3668 872.1267) 
(list 4480.3876 872.1369) 
(list 4480.4097 872.1472) 
(list 4480.4327 872.1575) 
(list 4480.4557 872.1678) 
(list 4480.4782 872.1781) 
(list 4480.4993 872.1883) 
(list 4480.5185 872.1986) 
(list 4480.5351 872.2089) 
(list 4480.5487 872.2192) 
(list 4480.5589 872.2294) 
(list 4480.5652 872.2397) 
(list 4480.5675 872.25) 
(list 4480.5675 872.25)))
(apply 'command (append '("pline") coords '("c")))
(setq tap14 (ssadd (entlast) tap14))
(command "_mirror" (entlast) "" "4480,900" "4480,901" "No")
(setq tap14 (ssadd (entlast) tap14))
(setq coords (list 
(list 4481.135 871.88) 
(list 4480.5675 871.88) 
(list 4480.5675 871.8903) 
(list 4480.5675 871.9006) 
(list 4480.5675 871.9108) 
(list 4480.5675 871.9211) 
(list 4480.5675 871.9314) 
(list 4480.5675 871.9417) 
(list 4480.5675 871.9519) 
(list 4480.5675 871.9622) 
(list 4480.5675 871.9725) 
(list 4480.5675 871.9828) 
(list 4480.5675 871.9931) 
(list 4480.5675 872.0033) 
(list 4480.5675 872.0136) 
(list 4480.5675 872.0239) 
(list 4480.5675 872.0342) 
(list 4480.5675 872.0444) 
(list 4480.5675 872.0547) 
(list 4480.5675 872.065) 
(list 4480.5675 872.0753) 
(list 4480.5675 872.0856) 
(list 4480.5675 872.0958) 
(list 4480.5675 872.1061) 
(list 4480.5675 872.1164) 
(list 4480.5675 872.1267) 
(list 4480.5675 872.1369) 
(list 4480.5675 872.1472) 
(list 4480.5675 872.1575) 
(list 4480.5675 872.1678) 
(list 4480.5675 872.1781) 
(list 4480.5675 872.1883) 
(list 4480.5675 872.1986) 
(list 4480.5675 872.2089) 
(list 4480.5675 872.2192) 
(list 4480.5675 872.2294) 
(list 4480.5675 872.2397) 
(list 4480.5675 872.25) 
(list 4481.135 872.25)))
(apply 'command (append '("pline") coords '("c")))
(setq tap14 (ssadd (entlast) tap14))
(command "_mirror" (entlast) "" "4480,900" "4480,901" "No")
(setq tap14 (ssadd (entlast) tap14))
(command "_block" "blktap14" "4480,900" tap14 "")
(command "_insert" "blktap14" "4480,900" "1" "1" "0")
(command "_insert" "blktap14" "4480,900" "1" "1" "180")
(setq uc14 nil)
(setq uc14 (ssadd))
(setq coords (list 
(list 0 -0.185) 
(list 0.135 -0.185) 
(list 0.135 -0.17472) 
(list 0.135 -0.16444) 
(list 0.135 -0.15417) 
(list 0.135 -0.14389) 
(list 0.135 -0.13361) 
(list 0.135 -0.12333) 
(list 0.135 -0.11306) 
(list 0.135 -0.10278) 
(list 0.135 -0.0925) 
(list 0.135 -0.082222) 
(list 0.135 -0.071944) 
(list 0.135 -0.061667) 
(list 0.135 -0.051389) 
(list 0.135 -0.041111) 
(list 0.135 -0.030833) 
(list 0.135 -0.020556) 
(list 0.135 -0.010278) 
(list 0.135 0) 
(list 0.135 0.010278) 
(list 0.135 0.020556) 
(list 0.135 0.030833) 
(list 0.135 0.041111) 
(list 0.135 0.051389) 
(list 0.135 0.061667) 
(list 0.135 0.071944) 
(list 0.135 0.082222) 
(list 0.135 0.0925) 
(list 0.135 0.10278) 
(list 0.135 0.11306) 
(list 0.135 0.12333) 
(list 0.135 0.13361) 
(list 0.135 0.14389) 
(list 0.135 0.15417) 
(list 0.135 0.16444) 
(list 0.135 0.17472) 
(list 0.135 0.185) 
(list 0 0.185)))
(apply 'command (append '("pline") coords '("c")))
(setq uc14 (ssadd (entlast) uc14))
(setq coords (list 
(list 1.135 -0.185) 
(list 0.5675 -0.185) 
(list 0.56546 -0.17472) 
(list 0.55939 -0.16444) 
(list 0.54948 -0.15417) 
(list 0.53603 -0.14389) 
(list 0.51946 -0.13361) 
(list 0.50025 -0.12333) 
(list 0.479 -0.11306) 
(list 0.45636 -0.10278) 
(list 0.433 -0.0925) 
(list 0.40964 -0.082222) 
(list 0.387 -0.071944) 
(list 0.36575 -0.061667) 
(list 0.34654 -0.051389) 
(list 0.32997 -0.041111) 
(list 0.31652 -0.030833) 
(list 0.30661 -0.020556) 
(list 0.30054 -0.010278) 
(list 0.2985 0) 
(list 0.30054 0.010278) 
(list 0.30661 0.020556) 
(list 0.31652 0.030833) 
(list 0.32997 0.041111) 
(list 0.34654 0.051389) 
(list 0.36575 0.061667) 
(list 0.387 0.071944) 
(list 0.40964 0.082222) 
(list 0.433 0.0925) 
(list 0.45636 0.10278) 
(list 0.479 0.11306) 
(list 0.50025 0.12333) 
(list 0.51946 0.13361) 
(list 0.53603 0.14389) 
(list 0.54948 0.15417) 
(list 0.55939 0.16444) 
(list 0.56546 0.17472) 
(list 0.5675 0.185) 
(list 1.135 0.185)))
(apply 'command (append '("pline") coords '("c")))
(setq uc14 (ssadd (entlast) uc14))
(command "_block" "blkuc14" "0,0.185" uc14 "")
(command "_insert" "blkuc14" "4480,872.62" "1" "1" "0")
(command "_insert" "blkuc14" "4480,872.25" "1" "1" "180")
(command "_insert" "blkuc14" "4480,872.99" "1" "1" "0")
(command "_insert" "blkuc14" "4480,872.62" "1" "1" "180")
(command "_insert" "blkuc14" "4480,873.36" "1" "1" "0")
(command "_insert" "blkuc14" "4480,872.99" "1" "1" "180")
(command "_insert" "blkuc14" "4480,873.73" "1" "1" "0")
(command "_insert" "blkuc14" "4480,873.36" "1" "1" "180")
(command "_insert" "blkuc14" "4480,874.1" "1" "1" "0")
(command "_insert" "blkuc14" "4480,873.73" "1" "1" "180")
(command "_insert" "blkuc14" "4480,874.47" "1" "1" "0")
(command "_insert" "blkuc14" "4480,874.1" "1" "1" "180")
(command "_insert" "blkuc14" "4480,874.84" "1" "1" "0")
(command "_insert" "blkuc14" "4480,874.47" "1" "1" "180")
(command "_insert" "blkuc14" "4480,875.21" "1" "1" "0")
(command "_insert" "blkuc14" "4480,874.84" "1" "1" "180")
(command "_insert" "blkuc14" "4480,875.58" "1" "1" "0")
(command "_insert" "blkuc14" "4480,875.21" "1" "1" "180")
(command "_insert" "blkuc14" "4480,875.95" "1" "1" "0")
(command "_insert" "blkuc14" "4480,875.58" "1" "1" "180")
(command "_insert" "blkuc14" "4480,876.32" "1" "1" "0")
(command "_insert" "blkuc14" "4480,875.95" "1" "1" "180")
(command "_insert" "blkuc14" "4480,876.69" "1" "1" "0")
(command "_insert" "blkuc14" "4480,876.32" "1" "1" "180")
(command "_insert" "blkuc14" "4480,877.06" "1" "1" "0")
(command "_insert" "blkuc14" "4480,876.69" "1" "1" "180")
(command "_insert" "blkuc14" "4480,877.43" "1" "1" "0")
(command "_insert" "blkuc14" "4480,877.06" "1" "1" "180")
(command "_insert" "blkuc14" "4480,877.8" "1" "1" "0")
(command "_insert" "blkuc14" "4480,877.43" "1" "1" "180")
(command "_insert" "blkuc14" "4480,878.17" "1" "1" "0")
(command "_insert" "blkuc14" "4480,877.8" "1" "1" "180")
(command "_insert" "blkuc14" "4480,878.54" "1" "1" "0")
(command "_insert" "blkuc14" "4480,878.17" "1" "1" "180")
(command "_insert" "blkuc14" "4480,878.91" "1" "1" "0")
(command "_insert" "blkuc14" "4480,878.54" "1" "1" "180")
(command "_insert" "blkuc14" "4480,879.28" "1" "1" "0")
(command "_insert" "blkuc14" "4480,878.91" "1" "1" "180")
(command "_insert" "blkuc14" "4480,879.65" "1" "1" "0")
(command "_insert" "blkuc14" "4480,879.28" "1" "1" "180")
(command "_insert" "blkuc14" "4480,880.02" "1" "1" "0")
(command "_insert" "blkuc14" "4480,879.65" "1" "1" "180")
(command "_insert" "blkuc14" "4480,880.39" "1" "1" "0")
(command "_insert" "blkuc14" "4480,880.02" "1" "1" "180")
(command "_insert" "blkuc14" "4480,880.76" "1" "1" "0")
(command "_insert" "blkuc14" "4480,880.39" "1" "1" "180")
(command "_insert" "blkuc14" "4480,881.13" "1" "1" "0")
(command "_insert" "blkuc14" "4480,880.76" "1" "1" "180")
(command "_insert" "blkuc14" "4480,881.5" "1" "1" "0")
(command "_insert" "blkuc14" "4480,881.13" "1" "1" "180")
(command "_insert" "blkuc14" "4480,881.87" "1" "1" "0")
(command "_insert" "blkuc14" "4480,881.5" "1" "1" "180")
(command "_insert" "blkuc14" "4480,882.24" "1" "1" "0")
(command "_insert" "blkuc14" "4480,881.87" "1" "1" "180")
(command "_insert" "blkuc14" "4480,882.61" "1" "1" "0")
(command "_insert" "blkuc14" "4480,882.24" "1" "1" "180")
(command "_insert" "blkuc14" "4480,882.98" "1" "1" "0")
(command "_insert" "blkuc14" "4480,882.61" "1" "1" "180")
(command "_insert" "blkuc14" "4480,883.35" "1" "1" "0")
(command "_insert" "blkuc14" "4480,882.98" "1" "1" "180")
(command "_insert" "blkuc14" "4480,883.72" "1" "1" "0")
(command "_insert" "blkuc14" "4480,883.35" "1" "1" "180")
(command "_insert" "blkuc14" "4480,884.09" "1" "1" "0")
(command "_insert" "blkuc14" "4480,883.72" "1" "1" "180")
(command "_insert" "blkuc14" "4480,884.46" "1" "1" "0")
(command "_insert" "blkuc14" "4480,884.09" "1" "1" "180")
(command "_insert" "blkuc14" "4480,884.83" "1" "1" "0")
(command "_insert" "blkuc14" "4480,884.46" "1" "1" "180")
(command "_insert" "blkuc14" "4480,885.2" "1" "1" "0")
(command "_insert" "blkuc14" "4480,884.83" "1" "1" "180")
(command "_insert" "blkuc14" "4480,885.57" "1" "1" "0")
(command "_insert" "blkuc14" "4480,885.2" "1" "1" "180")
(command "_insert" "blkuc14" "4480,885.94" "1" "1" "0")
(command "_insert" "blkuc14" "4480,885.57" "1" "1" "180")
(command "_insert" "blkuc14" "4480,886.31" "1" "1" "0")
(command "_insert" "blkuc14" "4480,885.94" "1" "1" "180")
(command "_insert" "blkuc14" "4480,886.68" "1" "1" "0")
(command "_insert" "blkuc14" "4480,886.31" "1" "1" "180")
(command "_insert" "blkuc14" "4480,887.05" "1" "1" "0")
(command "_insert" "blkuc14" "4480,886.68" "1" "1" "180")
(command "_insert" "blkuc14" "4480,887.42" "1" "1" "0")
(command "_insert" "blkuc14" "4480,887.05" "1" "1" "180")
(command "_insert" "blkuc14" "4480,887.79" "1" "1" "0")
(command "_insert" "blkuc14" "4480,887.42" "1" "1" "180")
(command "_insert" "blkuc14" "4480,888.16" "1" "1" "0")
(command "_insert" "blkuc14" "4480,887.79" "1" "1" "180")
(command "_insert" "blkuc14" "4480,888.53" "1" "1" "0")
(command "_insert" "blkuc14" "4480,888.16" "1" "1" "180")
(command "_insert" "blkuc14" "4480,888.9" "1" "1" "0")
(command "_insert" "blkuc14" "4480,888.53" "1" "1" "180")
(command "_insert" "blkuc14" "4480,889.27" "1" "1" "0")
(command "_insert" "blkuc14" "4480,888.9" "1" "1" "180")
(command "_insert" "blkuc14" "4480,889.64" "1" "1" "0")
(command "_insert" "blkuc14" "4480,889.27" "1" "1" "180")
(command "_insert" "blkuc14" "4480,890.01" "1" "1" "0")
(command "_insert" "blkuc14" "4480,889.64" "1" "1" "180")
(command "_insert" "blkuc14" "4480,890.38" "1" "1" "0")
(command "_insert" "blkuc14" "4480,890.01" "1" "1" "180")
(command "_insert" "blkuc14" "4480,890.75" "1" "1" "0")
(command "_insert" "blkuc14" "4480,890.38" "1" "1" "180")
(command "_insert" "blkuc14" "4480,891.12" "1" "1" "0")
(command "_insert" "blkuc14" "4480,890.75" "1" "1" "180")
(command "_insert" "blkuc14" "4480,891.49" "1" "1" "0")
(command "_insert" "blkuc14" "4480,891.12" "1" "1" "180")
(command "_insert" "blkuc14" "4480,891.86" "1" "1" "0")
(command "_insert" "blkuc14" "4480,891.49" "1" "1" "180")
(command "_insert" "blkuc14" "4480,892.23" "1" "1" "0")
(command "_insert" "blkuc14" "4480,891.86" "1" "1" "180")
(command "_insert" "blkuc14" "4480,892.6" "1" "1" "0")
(command "_insert" "blkuc14" "4480,892.23" "1" "1" "180")
(command "_insert" "blkuc14" "4480,892.97" "1" "1" "0")
(command "_insert" "blkuc14" "4480,892.6" "1" "1" "180")
(command "_insert" "blkuc14" "4480,893.34" "1" "1" "0")
(command "_insert" "blkuc14" "4480,892.97" "1" "1" "180")
(command "_insert" "blkuc14" "4480,893.71" "1" "1" "0")
(command "_insert" "blkuc14" "4480,893.34" "1" "1" "180")
(command "_insert" "blkuc14" "4480,894.08" "1" "1" "0")
(command "_insert" "blkuc14" "4480,893.71" "1" "1" "180")
(command "_insert" "blkuc14" "4480,894.45" "1" "1" "0")
(command "_insert" "blkuc14" "4480,894.08" "1" "1" "180")
(command "_insert" "blkuc14" "4480,894.82" "1" "1" "0")
(command "_insert" "blkuc14" "4480,894.45" "1" "1" "180")
(command "_insert" "blkuc14" "4480,895.19" "1" "1" "0")
(command "_insert" "blkuc14" "4480,894.82" "1" "1" "180")
(command "_insert" "blkuc14" "4480,895.56" "1" "1" "0")
(command "_insert" "blkuc14" "4480,895.19" "1" "1" "180")
(command "_insert" "blkuc14" "4480,895.93" "1" "1" "0")
(command "_insert" "blkuc14" "4480,895.56" "1" "1" "180")
(command "_insert" "blkuc14" "4480,896.3" "1" "1" "0")
(command "_insert" "blkuc14" "4480,895.93" "1" "1" "180")
(command "_insert" "blkuc14" "4480,896.67" "1" "1" "0")
(command "_insert" "blkuc14" "4480,896.3" "1" "1" "180")
(command "_insert" "blkuc14" "4480,897.04" "1" "1" "0")
(command "_insert" "blkuc14" "4480,896.67" "1" "1" "180")
(command "_insert" "blkuc14" "4480,897.41" "1" "1" "0")
(command "_insert" "blkuc14" "4480,897.04" "1" "1" "180")
(command "_insert" "blkuc14" "4480,897.78" "1" "1" "0")
(command "_insert" "blkuc14" "4480,897.41" "1" "1" "180")
(command "_insert" "blkuc14" "4480,898.15" "1" "1" "0")
(command "_insert" "blkuc14" "4480,897.78" "1" "1" "180")
(command "_insert" "blkuc14" "4480,898.52" "1" "1" "0")
(command "_insert" "blkuc14" "4480,898.15" "1" "1" "180")
(command "_insert" "blkuc14" "4480,898.89" "1" "1" "0")
(command "_insert" "blkuc14" "4480,898.52" "1" "1" "180")
(command "_insert" "blkuc14" "4480,899.26" "1" "1" "0")
(command "_insert" "blkuc14" "4480,898.89" "1" "1" "180")
(command "_insert" "blkuc14" "4480,899.63" "1" "1" "0")
(command "_insert" "blkuc14" "4480,899.26" "1" "1" "180")
(command "_insert" "blkuc14" "4480,900" "1" "1" "0")
(command "_insert" "blkuc14" "4480,899.63" "1" "1" "180")
(command "_insert" "blkuc14" "4480,900.37" "1" "1" "0")
(command "_insert" "blkuc14" "4480,900" "1" "1" "180")
(command "_insert" "blkuc14" "4480,900.74" "1" "1" "0")
(command "_insert" "blkuc14" "4480,900.37" "1" "1" "180")
(command "_insert" "blkuc14" "4480,901.11" "1" "1" "0")
(command "_insert" "blkuc14" "4480,900.74" "1" "1" "180")
(command "_insert" "blkuc14" "4480,901.48" "1" "1" "0")
(command "_insert" "blkuc14" "4480,901.11" "1" "1" "180")
(command "_insert" "blkuc14" "4480,901.85" "1" "1" "0")
(command "_insert" "blkuc14" "4480,901.48" "1" "1" "180")
(command "_insert" "blkuc14" "4480,902.22" "1" "1" "0")
(command "_insert" "blkuc14" "4480,901.85" "1" "1" "180")
(command "_insert" "blkuc14" "4480,902.59" "1" "1" "0")
(command "_insert" "blkuc14" "4480,902.22" "1" "1" "180")
(command "_insert" "blkuc14" "4480,902.96" "1" "1" "0")
(command "_insert" "blkuc14" "4480,902.59" "1" "1" "180")
(command "_insert" "blkuc14" "4480,903.33" "1" "1" "0")
(command "_insert" "blkuc14" "4480,902.96" "1" "1" "180")
(command "_insert" "blkuc14" "4480,903.7" "1" "1" "0")
(command "_insert" "blkuc14" "4480,903.33" "1" "1" "180")
(command "_insert" "blkuc14" "4480,904.07" "1" "1" "0")
(command "_insert" "blkuc14" "4480,903.7" "1" "1" "180")
(command "_insert" "blkuc14" "4480,904.44" "1" "1" "0")
(command "_insert" "blkuc14" "4480,904.07" "1" "1" "180")
(command "_insert" "blkuc14" "4480,904.81" "1" "1" "0")
(command "_insert" "blkuc14" "4480,904.44" "1" "1" "180")
(command "_insert" "blkuc14" "4480,905.18" "1" "1" "0")
(command "_insert" "blkuc14" "4480,904.81" "1" "1" "180")
(command "_insert" "blkuc14" "4480,905.55" "1" "1" "0")
(command "_insert" "blkuc14" "4480,905.18" "1" "1" "180")
(command "_insert" "blkuc14" "4480,905.92" "1" "1" "0")
(command "_insert" "blkuc14" "4480,905.55" "1" "1" "180")
(command "_insert" "blkuc14" "4480,906.29" "1" "1" "0")
(command "_insert" "blkuc14" "4480,905.92" "1" "1" "180")
(command "_insert" "blkuc14" "4480,906.66" "1" "1" "0")
(command "_insert" "blkuc14" "4480,906.29" "1" "1" "180")
(command "_insert" "blkuc14" "4480,907.03" "1" "1" "0")
(command "_insert" "blkuc14" "4480,906.66" "1" "1" "180")
(command "_insert" "blkuc14" "4480,907.4" "1" "1" "0")
(command "_insert" "blkuc14" "4480,907.03" "1" "1" "180")
(command "_insert" "blkuc14" "4480,907.77" "1" "1" "0")
(command "_insert" "blkuc14" "4480,907.4" "1" "1" "180")
(command "_insert" "blkuc14" "4480,908.14" "1" "1" "0")
(command "_insert" "blkuc14" "4480,907.77" "1" "1" "180")
(command "_insert" "blkuc14" "4480,908.51" "1" "1" "0")
(command "_insert" "blkuc14" "4480,908.14" "1" "1" "180")
(command "_insert" "blkuc14" "4480,908.88" "1" "1" "0")
(command "_insert" "blkuc14" "4480,908.51" "1" "1" "180")
(command "_insert" "blkuc14" "4480,909.25" "1" "1" "0")
(command "_insert" "blkuc14" "4480,908.88" "1" "1" "180")
(command "_insert" "blkuc14" "4480,909.62" "1" "1" "0")
(command "_insert" "blkuc14" "4480,909.25" "1" "1" "180")
(command "_insert" "blkuc14" "4480,909.99" "1" "1" "0")
(command "_insert" "blkuc14" "4480,909.62" "1" "1" "180")
(command "_insert" "blkuc14" "4480,910.36" "1" "1" "0")
(command "_insert" "blkuc14" "4480,909.99" "1" "1" "180")
(command "_insert" "blkuc14" "4480,910.73" "1" "1" "0")
(command "_insert" "blkuc14" "4480,910.36" "1" "1" "180")
(command "_insert" "blkuc14" "4480,911.1" "1" "1" "0")
(command "_insert" "blkuc14" "4480,910.73" "1" "1" "180")
(command "_insert" "blkuc14" "4480,911.47" "1" "1" "0")
(command "_insert" "blkuc14" "4480,911.1" "1" "1" "180")
(command "_insert" "blkuc14" "4480,911.84" "1" "1" "0")
(command "_insert" "blkuc14" "4480,911.47" "1" "1" "180")
(command "_insert" "blkuc14" "4480,912.21" "1" "1" "0")
(command "_insert" "blkuc14" "4480,911.84" "1" "1" "180")
(command "_insert" "blkuc14" "4480,912.58" "1" "1" "0")
(command "_insert" "blkuc14" "4480,912.21" "1" "1" "180")
(command "_insert" "blkuc14" "4480,912.95" "1" "1" "0")
(command "_insert" "blkuc14" "4480,912.58" "1" "1" "180")
(command "_insert" "blkuc14" "4480,913.32" "1" "1" "0")
(command "_insert" "blkuc14" "4480,912.95" "1" "1" "180")
(command "_insert" "blkuc14" "4480,913.69" "1" "1" "0")
(command "_insert" "blkuc14" "4480,913.32" "1" "1" "180")
(command "_insert" "blkuc14" "4480,914.06" "1" "1" "0")
(command "_insert" "blkuc14" "4480,913.69" "1" "1" "180")
(command "_insert" "blkuc14" "4480,914.43" "1" "1" "0")
(command "_insert" "blkuc14" "4480,914.06" "1" "1" "180")
(command "_insert" "blkuc14" "4480,914.8" "1" "1" "0")
(command "_insert" "blkuc14" "4480,914.43" "1" "1" "180")
(command "_insert" "blkuc14" "4480,915.17" "1" "1" "0")
(command "_insert" "blkuc14" "4480,914.8" "1" "1" "180")
(command "_insert" "blkuc14" "4480,915.54" "1" "1" "0")
(command "_insert" "blkuc14" "4480,915.17" "1" "1" "180")
(command "_insert" "blkuc14" "4480,915.91" "1" "1" "0")
(command "_insert" "blkuc14" "4480,915.54" "1" "1" "180")
(command "_insert" "blkuc14" "4480,916.28" "1" "1" "0")
(command "_insert" "blkuc14" "4480,915.91" "1" "1" "180")
(command "_insert" "blkuc14" "4480,916.65" "1" "1" "0")
(command "_insert" "blkuc14" "4480,916.28" "1" "1" "180")
(command "_insert" "blkuc14" "4480,917.02" "1" "1" "0")
(command "_insert" "blkuc14" "4480,916.65" "1" "1" "180")
(command "_insert" "blkuc14" "4480,917.39" "1" "1" "0")
(command "_insert" "blkuc14" "4480,917.02" "1" "1" "180")
(command "_insert" "blkuc14" "4480,917.76" "1" "1" "0")
(command "_insert" "blkuc14" "4480,917.39" "1" "1" "180")
(command "_insert" "blkuc14" "4480,918.13" "1" "1" "0")
(command "_insert" "blkuc14" "4480,917.76" "1" "1" "180")
(command "_insert" "blkuc14" "4480,918.5" "1" "1" "0")
(command "_insert" "blkuc14" "4480,918.13" "1" "1" "180")
(command "_insert" "blkuc14" "4480,918.87" "1" "1" "0")
(command "_insert" "blkuc14" "4480,918.5" "1" "1" "180")
(command "_insert" "blkuc14" "4480,919.24" "1" "1" "0")
(command "_insert" "blkuc14" "4480,918.87" "1" "1" "180")
(command "_insert" "blkuc14" "4480,919.61" "1" "1" "0")
(command "_insert" "blkuc14" "4480,919.24" "1" "1" "180")
(command "_insert" "blkuc14" "4480,919.98" "1" "1" "0")
(command "_insert" "blkuc14" "4480,919.61" "1" "1" "180")
(command "_insert" "blkuc14" "4480,920.35" "1" "1" "0")
(command "_insert" "blkuc14" "4480,919.98" "1" "1" "180")
(command "_insert" "blkuc14" "4480,920.72" "1" "1" "0")
(command "_insert" "blkuc14" "4480,920.35" "1" "1" "180")
(command "_insert" "blkuc14" "4480,921.09" "1" "1" "0")
(command "_insert" "blkuc14" "4480,920.72" "1" "1" "180")
(command "_insert" "blkuc14" "4480,921.46" "1" "1" "0")
(command "_insert" "blkuc14" "4480,921.09" "1" "1" "180")
(command "_insert" "blkuc14" "4480,921.83" "1" "1" "0")
(command "_insert" "blkuc14" "4480,921.46" "1" "1" "180")
(command "_insert" "blkuc14" "4480,922.2" "1" "1" "0")
(command "_insert" "blkuc14" "4480,921.83" "1" "1" "180")
(command "_insert" "blkuc14" "4480,922.57" "1" "1" "0")
(command "_insert" "blkuc14" "4480,922.2" "1" "1" "180")
(command "_insert" "blkuc14" "4480,922.94" "1" "1" "0")
(command "_insert" "blkuc14" "4480,922.57" "1" "1" "180")
(command "_insert" "blkuc14" "4480,923.31" "1" "1" "0")
(command "_insert" "blkuc14" "4480,922.94" "1" "1" "180")
(command "_insert" "blkuc14" "4480,923.68" "1" "1" "0")
(command "_insert" "blkuc14" "4480,923.31" "1" "1" "180")
(command "_insert" "blkuc14" "4480,924.05" "1" "1" "0")
(command "_insert" "blkuc14" "4480,923.68" "1" "1" "180")
(command "_insert" "blkuc14" "4480,924.42" "1" "1" "0")
(command "_insert" "blkuc14" "4480,924.05" "1" "1" "180")
(command "_insert" "blkuc14" "4480,924.79" "1" "1" "0")
(command "_insert" "blkuc14" "4480,924.42" "1" "1" "180")
(command "_insert" "blkuc14" "4480,925.16" "1" "1" "0")
(command "_insert" "blkuc14" "4480,924.79" "1" "1" "180")
(command "_insert" "blkuc14" "4480,925.53" "1" "1" "0")
(command "_insert" "blkuc14" "4480,925.16" "1" "1" "180")
(command "_insert" "blkuc14" "4480,925.9" "1" "1" "0")
(command "_insert" "blkuc14" "4480,925.53" "1" "1" "180")
(command "_insert" "blkuc14" "4480,926.27" "1" "1" "0")
(command "_insert" "blkuc14" "4480,925.9" "1" "1" "180")
(command "_insert" "blkuc14" "4480,926.64" "1" "1" "0")
(command "_insert" "blkuc14" "4480,926.27" "1" "1" "180")
(command "_insert" "blkuc14" "4480,927.01" "1" "1" "0")
(command "_insert" "blkuc14" "4480,926.64" "1" "1" "180")
(command "_insert" "blkuc14" "4480,927.38" "1" "1" "0")
(command "_insert" "blkuc14" "4480,927.01" "1" "1" "180")
(command "_insert" "blkuc14" "4480,927.75" "1" "1" "0")
(command "_insert" "blkuc14" "4480,927.38" "1" "1" "180")
(command "_layer" "set" "phccover" "")
(command "_rectangle" "4478.865,933.3" "4481.135,866.7")
(command "_layer" "set" "nitride" "")
(setq phc14 currobj)
(command "_layer" "set" "cover" "")
(command "_rectangle" "4478.865,836.7" "4481.135,963.3")
(command "_layer" "set" "nitride" "")
(command "_layer" "set" "text" "")
(command "_circle" "4477.915,846.7" "0.075")
(command "_circle" "4477.54,846.7" "0.15")
(command "_circle" "4477.165,846.7" "0.075")
(command "_circle" "4476.79,846.7" "0.15")
(command "_circle" "4477.915,848.7" "0.075")
(command "_circle" "4477.54,848.7" "0.075")
(command "_circle" "4477.165,848.7" "0.15")
(command "_circle" "4476.79,848.7" "0.15")
(command "_circle" "4477.915,850.7" "0.075")
(command "_circle" "4477.54,850.7" "0.15")
(command "_circle" "4477.165,850.7" "0.15")
(command "_circle" "4476.79,850.7" "0.15")
(command "_circle" "4477.915,852.7" "0.075")
(command "_circle" "4477.54,852.7" "0.075")
(command "_circle" "4477.165,852.7" "0.075")
(command "_circle" "4476.79,852.7" "0.075")
(command "_circle" "4476.415,852.7" "0.15")
(command "_circle" "4477.915,854.7" "0.075")
(command "_circle" "4477.54,854.7" "0.15")
(command "_circle" "4477.165,854.7" "0.075")
(command "_circle" "4476.79,854.7" "0.075")
(command "_circle" "4476.415,854.7" "0.15")
(command "_circle" "4477.915,856.7" "0.075")
(command "_circle" "4477.54,856.7" "0.075")
(command "_circle" "4477.165,856.7" "0.15")
(command "_circle" "4476.79,856.7" "0.075")
(command "_circle" "4476.415,856.7" "0.15")
(command "_circle" "4477.915,858.7" "0.075")
(command "_circle" "4477.54,858.7" "0.15")
(command "_circle" "4477.165,858.7" "0.15")
(command "_circle" "4476.79,858.7" "0.075")
(command "_circle" "4476.415,858.7" "0.15")
(command "_circle" "4477.915,860.7" "0.075")
(command "_circle" "4477.54,860.7" "0.075")
(command "_circle" "4477.165,860.7" "0.075")
(command "_circle" "4476.79,860.7" "0.15")
(command "_circle" "4476.415,860.7" "0.15")
(command "_circle" "4477.915,862.7" "0.075")
(command "_circle" "4477.54,862.7" "0.15")
(command "_circle" "4477.165,862.7" "0.075")
(command "_circle" "4476.79,862.7" "0.15")
(command "_circle" "4476.415,862.7" "0.15")
(command "_circle" "4477.915,864.7" "0.075")
(command "_circle" "4477.54,864.7" "0.075")
(command "_circle" "4477.165,864.7" "0.15")
(command "_circle" "4476.79,864.7" "0.15")
(command "_circle" "4476.415,864.7" "0.15")
(command "_circle" "4477.915,866.7" "0.075")
(command "_circle" "4477.54,866.7" "0.15")
(command "_circle" "4477.165,866.7" "0.15")
(command "_circle" "4476.79,866.7" "0.15")
(command "_circle" "4476.415,866.7" "0.15")
(command "_circle" "4477.915,868.7" "0.075")
(command "_circle" "4477.54,868.7" "0.075")
(command "_circle" "4477.165,868.7" "0.075")
(command "_circle" "4476.79,868.7" "0.075")
(command "_circle" "4476.415,868.7" "0.075")
(command "_circle" "4476.04,868.7" "0.15")
(command "_circle" "4477.915,870.7" "0.075")
(command "_circle" "4477.54,870.7" "0.15")
(command "_circle" "4477.165,870.7" "0.075")
(command "_circle" "4476.79,870.7" "0.075")
(command "_circle" "4476.415,870.7" "0.075")
(command "_circle" "4476.04,870.7" "0.15")
(command "_circle" "4477.915,872.7" "0.075")
(command "_circle" "4477.54,872.7" "0.075")
(command "_circle" "4477.165,872.7" "0.15")
(command "_circle" "4476.79,872.7" "0.075")
(command "_circle" "4476.415,872.7" "0.075")
(command "_circle" "4476.04,872.7" "0.15")
(command "_circle" "4477.915,874.7" "0.075")
(command "_circle" "4477.54,874.7" "0.15")
(command "_circle" "4477.165,874.7" "0.15")
(command "_circle" "4476.79,874.7" "0.075")
(command "_circle" "4476.415,874.7" "0.075")
(command "_circle" "4476.04,874.7" "0.15")
(command "_circle" "4477.915,876.7" "0.075")
(command "_circle" "4477.54,876.7" "0.075")
(command "_circle" "4477.165,876.7" "0.075")
(command "_circle" "4476.79,876.7" "0.15")
(command "_circle" "4476.415,876.7" "0.075")
(command "_circle" "4476.04,876.7" "0.15")
(command "_circle" "4477.915,878.7" "0.075")
(command "_circle" "4477.54,878.7" "0.15")
(command "_circle" "4477.165,878.7" "0.075")
(command "_circle" "4476.79,878.7" "0.15")
(command "_circle" "4476.415,878.7" "0.075")
(command "_circle" "4476.04,878.7" "0.15")
(command "_circle" "4477.915,880.7" "0.075")
(command "_circle" "4477.54,880.7" "0.075")
(command "_circle" "4477.165,880.7" "0.15")
(command "_circle" "4476.79,880.7" "0.15")
(command "_circle" "4476.415,880.7" "0.075")
(command "_circle" "4476.04,880.7" "0.15")
(command "_circle" "4477.915,882.7" "0.075")
(command "_circle" "4477.54,882.7" "0.15")
(command "_circle" "4477.165,882.7" "0.15")
(command "_circle" "4476.79,882.7" "0.15")
(command "_circle" "4476.415,882.7" "0.075")
(command "_circle" "4476.04,882.7" "0.15")
(command "_circle" "4477.915,884.7" "0.075")
(command "_circle" "4477.54,884.7" "0.075")
(command "_circle" "4477.165,884.7" "0.075")
(command "_circle" "4476.79,884.7" "0.075")
(command "_circle" "4476.415,884.7" "0.15")
(command "_circle" "4476.04,884.7" "0.15")
(command "_circle" "4477.915,886.7" "0.075")
(command "_circle" "4477.54,886.7" "0.15")
(command "_circle" "4477.165,886.7" "0.075")
(command "_circle" "4476.79,886.7" "0.075")
(command "_circle" "4476.415,886.7" "0.15")
(command "_circle" "4476.04,886.7" "0.15")
(command "_circle" "4477.915,888.7" "0.075")
(command "_circle" "4477.54,888.7" "0.075")
(command "_circle" "4477.165,888.7" "0.15")
(command "_circle" "4476.79,888.7" "0.075")
(command "_circle" "4476.415,888.7" "0.15")
(command "_circle" "4476.04,888.7" "0.15")
(command "_circle" "4477.915,890.7" "0.075")
(command "_circle" "4477.54,890.7" "0.15")
(command "_circle" "4477.165,890.7" "0.15")
(command "_circle" "4476.79,890.7" "0.075")
(command "_circle" "4476.415,890.7" "0.15")
(command "_circle" "4476.04,890.7" "0.15")
(command "_circle" "4477.915,892.7" "0.075")
(command "_circle" "4477.54,892.7" "0.075")
(command "_circle" "4477.165,892.7" "0.075")
(command "_circle" "4476.79,892.7" "0.15")
(command "_circle" "4476.415,892.7" "0.15")
(command "_circle" "4476.04,892.7" "0.15")
(command "_circle" "4477.915,894.7" "0.075")
(command "_circle" "4477.54,894.7" "0.15")
(command "_circle" "4477.165,894.7" "0.075")
(command "_circle" "4476.79,894.7" "0.15")
(command "_circle" "4476.415,894.7" "0.15")
(command "_circle" "4476.04,894.7" "0.15")
(command "_circle" "4477.915,896.7" "0.075")
(command "_circle" "4477.54,896.7" "0.075")
(command "_circle" "4477.165,896.7" "0.15")
(command "_circle" "4476.79,896.7" "0.15")
(command "_circle" "4476.415,896.7" "0.15")
(command "_circle" "4476.04,896.7" "0.15")
(command "_circle" "4477.915,898.7" "0.075")
(command "_circle" "4477.54,898.7" "0.15")
(command "_circle" "4477.165,898.7" "0.15")
(command "_circle" "4476.79,898.7" "0.15")
(command "_circle" "4476.415,898.7" "0.15")
(command "_circle" "4476.04,898.7" "0.15")
(command "_circle" "4477.915,900.7" "0.075")
(command "_circle" "4477.54,900.7" "0.075")
(command "_circle" "4477.165,900.7" "0.075")
(command "_circle" "4476.79,900.7" "0.075")
(command "_circle" "4476.415,900.7" "0.075")
(command "_circle" "4476.04,900.7" "0.075")
(command "_circle" "4475.665,900.7" "0.15")
(command "_circle" "4477.915,902.7" "0.075")
(command "_circle" "4477.54,902.7" "0.15")
(command "_circle" "4477.165,902.7" "0.075")
(command "_circle" "4476.79,902.7" "0.075")
(command "_circle" "4476.415,902.7" "0.075")
(command "_circle" "4476.04,902.7" "0.075")
(command "_circle" "4475.665,902.7" "0.15")
(command "_circle" "4477.915,904.7" "0.075")
(command "_circle" "4477.54,904.7" "0.075")
(command "_circle" "4477.165,904.7" "0.15")
(command "_circle" "4476.79,904.7" "0.075")
(command "_circle" "4476.415,904.7" "0.075")
(command "_circle" "4476.04,904.7" "0.075")
(command "_circle" "4475.665,904.7" "0.15")
(command "_circle" "4477.915,906.7" "0.075")
(command "_circle" "4477.54,906.7" "0.15")
(command "_circle" "4477.165,906.7" "0.15")
(command "_circle" "4476.79,906.7" "0.075")
(command "_circle" "4476.415,906.7" "0.075")
(command "_circle" "4476.04,906.7" "0.075")
(command "_circle" "4475.665,906.7" "0.15")
(command "_circle" "4477.915,908.7" "0.075")
(command "_circle" "4477.54,908.7" "0.075")
(command "_circle" "4477.165,908.7" "0.075")
(command "_circle" "4476.79,908.7" "0.15")
(command "_circle" "4476.415,908.7" "0.075")
(command "_circle" "4476.04,908.7" "0.075")
(command "_circle" "4475.665,908.7" "0.15")
(command "_circle" "4477.915,910.7" "0.075")
(command "_circle" "4477.54,910.7" "0.15")
(command "_circle" "4477.165,910.7" "0.075")
(command "_circle" "4476.79,910.7" "0.15")
(command "_circle" "4476.415,910.7" "0.075")
(command "_circle" "4476.04,910.7" "0.075")
(command "_circle" "4475.665,910.7" "0.15")
(command "_circle" "4477.915,912.7" "0.075")
(command "_circle" "4477.54,912.7" "0.075")
(command "_circle" "4477.165,912.7" "0.15")
(command "_circle" "4476.79,912.7" "0.15")
(command "_circle" "4476.415,912.7" "0.075")
(command "_circle" "4476.04,912.7" "0.075")
(command "_circle" "4475.665,912.7" "0.15")
(command "_circle" "4477.915,914.7" "0.075")
(command "_circle" "4477.54,914.7" "0.15")
(command "_circle" "4477.165,914.7" "0.15")
(command "_circle" "4476.79,914.7" "0.15")
(command "_circle" "4476.415,914.7" "0.075")
(command "_circle" "4476.04,914.7" "0.075")
(command "_circle" "4475.665,914.7" "0.15")
(command "_circle" "4477.915,916.7" "0.075")
(command "_circle" "4477.54,916.7" "0.075")
(command "_circle" "4477.165,916.7" "0.075")
(command "_circle" "4476.79,916.7" "0.075")
(command "_circle" "4476.415,916.7" "0.15")
(command "_circle" "4476.04,916.7" "0.075")
(command "_circle" "4475.665,916.7" "0.15")
(command "_circle" "4477.915,918.7" "0.075")
(command "_circle" "4477.54,918.7" "0.15")
(command "_circle" "4477.165,918.7" "0.075")
(command "_circle" "4476.79,918.7" "0.075")
(command "_circle" "4476.415,918.7" "0.15")
(command "_circle" "4476.04,918.7" "0.075")
(command "_circle" "4475.665,918.7" "0.15")
(command "_circle" "4477.915,920.7" "0.075")
(command "_circle" "4477.54,920.7" "0.075")
(command "_circle" "4477.165,920.7" "0.15")
(command "_circle" "4476.79,920.7" "0.075")
(command "_circle" "4476.415,920.7" "0.15")
(command "_circle" "4476.04,920.7" "0.075")
(command "_circle" "4475.665,920.7" "0.15")
(command "_circle" "4477.915,922.7" "0.075")
(command "_circle" "4477.54,922.7" "0.15")
(command "_circle" "4477.165,922.7" "0.15")
(command "_circle" "4476.79,922.7" "0.075")
(command "_circle" "4476.415,922.7" "0.15")
(command "_circle" "4476.04,922.7" "0.075")
(command "_circle" "4475.665,922.7" "0.15")
(command "_circle" "4477.915,924.7" "0.075")
(command "_circle" "4477.54,924.7" "0.075")
(command "_circle" "4477.165,924.7" "0.075")
(command "_circle" "4476.79,924.7" "0.15")
(command "_circle" "4476.415,924.7" "0.15")
(command "_circle" "4476.04,924.7" "0.075")
(command "_circle" "4475.665,924.7" "0.15")
(command "_circle" "4477.915,926.7" "0.075")
(command "_circle" "4477.54,926.7" "0.15")
(command "_circle" "4477.165,926.7" "0.075")
(command "_circle" "4476.79,926.7" "0.15")
(command "_circle" "4476.415,926.7" "0.15")
(command "_circle" "4476.04,926.7" "0.075")
(command "_circle" "4475.665,926.7" "0.15")
(command "_circle" "4477.915,928.7" "0.075")
(command "_circle" "4477.54,928.7" "0.075")
(command "_circle" "4477.165,928.7" "0.15")
(command "_circle" "4476.79,928.7" "0.15")
(command "_circle" "4476.415,928.7" "0.15")
(command "_circle" "4476.04,928.7" "0.075")
(command "_circle" "4475.665,928.7" "0.15")
(command "_circle" "4477.915,930.7" "0.075")
(command "_circle" "4477.54,930.7" "0.15")
(command "_circle" "4477.165,930.7" "0.15")
(command "_circle" "4476.79,930.7" "0.15")
(command "_circle" "4476.415,930.7" "0.15")
(command "_circle" "4476.04,930.7" "0.075")
(command "_circle" "4475.665,930.7" "0.15")
(command "_circle" "4477.915,932.7" "0.075")
(command "_circle" "4477.54,932.7" "0.075")
(command "_circle" "4477.165,932.7" "0.075")
(command "_circle" "4476.79,932.7" "0.075")
(command "_circle" "4476.415,932.7" "0.075")
(command "_circle" "4476.04,932.7" "0.15")
(command "_circle" "4475.665,932.7" "0.15")
(command "_circle" "4477.915,934.7" "0.075")
(command "_circle" "4477.54,934.7" "0.15")
(command "_circle" "4477.165,934.7" "0.075")
(command "_circle" "4476.79,934.7" "0.075")
(command "_circle" "4476.415,934.7" "0.075")
(command "_circle" "4476.04,934.7" "0.15")
(command "_circle" "4475.665,934.7" "0.15")
(command "_circle" "4477.915,936.7" "0.075")
(command "_circle" "4477.54,936.7" "0.075")
(command "_circle" "4477.165,936.7" "0.15")
(command "_circle" "4476.79,936.7" "0.075")
(command "_circle" "4476.415,936.7" "0.075")
(command "_circle" "4476.04,936.7" "0.15")
(command "_circle" "4475.665,936.7" "0.15")
(command "_circle" "4477.915,938.7" "0.075")
(command "_circle" "4477.54,938.7" "0.15")
(command "_circle" "4477.165,938.7" "0.15")
(command "_circle" "4476.79,938.7" "0.075")
(command "_circle" "4476.415,938.7" "0.075")
(command "_circle" "4476.04,938.7" "0.15")
(command "_circle" "4475.665,938.7" "0.15")
(command "_circle" "4477.915,940.7" "0.075")
(command "_circle" "4477.54,940.7" "0.075")
(command "_circle" "4477.165,940.7" "0.075")
(command "_circle" "4476.79,940.7" "0.15")
(command "_circle" "4476.415,940.7" "0.075")
(command "_circle" "4476.04,940.7" "0.15")
(command "_circle" "4475.665,940.7" "0.15")
(command "_circle" "4477.915,942.7" "0.075")
(command "_circle" "4477.54,942.7" "0.15")
(command "_circle" "4477.165,942.7" "0.075")
(command "_circle" "4476.79,942.7" "0.15")
(command "_circle" "4476.415,942.7" "0.075")
(command "_circle" "4476.04,942.7" "0.15")
(command "_circle" "4475.665,942.7" "0.15")
(command "_circle" "4477.915,944.7" "0.075")
(command "_circle" "4477.54,944.7" "0.075")
(command "_circle" "4477.165,944.7" "0.15")
(command "_circle" "4476.79,944.7" "0.15")
(command "_circle" "4476.415,944.7" "0.075")
(command "_circle" "4476.04,944.7" "0.15")
(command "_circle" "4475.665,944.7" "0.15")
(command "_circle" "4477.915,946.7" "0.075")
(command "_circle" "4477.54,946.7" "0.15")
(command "_circle" "4477.165,946.7" "0.15")
(command "_circle" "4476.79,946.7" "0.15")
(command "_circle" "4476.415,946.7" "0.075")
(command "_circle" "4476.04,946.7" "0.15")
(command "_circle" "4475.665,946.7" "0.15")
(command "_circle" "4477.915,948.7" "0.075")
(command "_circle" "4477.54,948.7" "0.075")
(command "_circle" "4477.165,948.7" "0.075")
(command "_circle" "4476.79,948.7" "0.075")
(command "_circle" "4476.415,948.7" "0.15")
(command "_circle" "4476.04,948.7" "0.15")
(command "_circle" "4475.665,948.7" "0.15")
(command "_circle" "4477.915,950.7" "0.075")
(command "_circle" "4477.54,950.7" "0.15")
(command "_circle" "4477.165,950.7" "0.075")
(command "_circle" "4476.79,950.7" "0.075")
(command "_circle" "4476.415,950.7" "0.15")
(command "_circle" "4476.04,950.7" "0.15")
(command "_circle" "4475.665,950.7" "0.15")
(command "_circle" "4477.915,952.7" "0.075")
(command "_circle" "4477.54,952.7" "0.075")
(command "_circle" "4477.165,952.7" "0.15")
(command "_circle" "4476.79,952.7" "0.075")
(command "_circle" "4476.415,952.7" "0.15")
(command "_circle" "4476.04,952.7" "0.15")
(command "_circle" "4475.665,952.7" "0.15")
(command "_circle" "4477.915,954.7" "0.075")
(command "_circle" "4477.54,954.7" "0.15")
(command "_circle" "4477.165,954.7" "0.15")
(command "_circle" "4476.79,954.7" "0.075")
(command "_circle" "4476.415,954.7" "0.15")
(command "_circle" "4476.04,954.7" "0.15")
(command "_circle" "4475.665,954.7" "0.15")
(command "_circle" "4477.915,956.7" "0.075")
(command "_circle" "4477.54,956.7" "0.075")
(command "_circle" "4477.165,956.7" "0.075")
(command "_circle" "4476.79,956.7" "0.15")
(command "_circle" "4476.415,956.7" "0.15")
(command "_circle" "4476.04,956.7" "0.15")
(command "_circle" "4475.665,956.7" "0.15")
(command "_circle" "4477.915,958.7" "0.075")
(command "_circle" "4477.54,958.7" "0.15")
(command "_circle" "4477.165,958.7" "0.075")
(command "_circle" "4476.79,958.7" "0.15")
(command "_circle" "4476.415,958.7" "0.15")
(command "_circle" "4476.04,958.7" "0.15")
(command "_circle" "4475.665,958.7" "0.15")
(command "_circle" "4477.915,960.7" "0.075")
(command "_circle" "4477.54,960.7" "0.075")
(command "_circle" "4477.165,960.7" "0.15")
(command "_circle" "4476.79,960.7" "0.15")
(command "_circle" "4476.415,960.7" "0.15")
(command "_circle" "4476.04,960.7" "0.15")
(command "_circle" "4475.665,960.7" "0.15")
(command "_circle" "4477.915,962.7" "0.075")
(command "_circle" "4477.54,962.7" "0.15")
(command "_circle" "4477.165,962.7" "0.15")
(command "_circle" "4476.79,962.7" "0.15")
(command "_circle" "4476.415,962.7" "0.15")
(command "_circle" "4476.04,962.7" "0.15")
(command "_circle" "4475.665,962.7" "0.15")
(command "_layer" "set" "nitride" "")
(command "_layer" "set" "text" "")
(command-s "_text" "4466.865,963.3" "2" "-90" "a = 370 nm" )
(sssetfirst nil (ssget "_L"))
(if (not (numberp (vl-string-search "Mac" (getvar "platform")))) (c:txtexp))
(command "_layer" "set" "nitride" "")
(command "_layer" "set" "text" "")
(command-s "_text" "4463.865,963.3" "2" "-90" "gap = 270 nm" )
(sssetfirst nil (ssget "_L"))
(if (not (numberp (vl-string-search "Mac" (getvar "platform")))) (c:txtexp))
(command "_layer" "set" "nitride" "")
(command "_layer" "set" "text" "")
(command-s "_text" "4460.865,963.3" "2" "-90" "amplitude = 134.5 nm" )
(sssetfirst nil (ssget "_L"))
(if (not (numberp (vl-string-search "Mac" (getvar "platform")))) (c:txtexp))
(command "_layer" "set" "nitride" "")
(command "_layer" "set" "text" "")
(command-s "_text" "4457.865,963.3" "2" "-90" "start width = 280 nm" )
(sssetfirst nil (ssget "_L"))
(if (not (numberp (vl-string-search "Mac" (getvar "platform")))) (c:txtexp))
(command "_layer" "set" "nitride" "")
(command "_layer" "set" "text" "")
(command-s "_text" "4454.865,963.3" "2" "-90" "width = 298 nm" )
(sssetfirst nil (ssget "_L"))
(if (not (numberp (vl-string-search "Mac" (getvar "platform")))) (c:txtexp))
(command "_layer" "set" "nitride" "")
(command "_layer" "set" "text" "")
(command-s "_text" "4451.865,963.3" "2" "-90" "taper: 15" )
(sssetfirst nil (ssget "_L"))
(if (not (numberp (vl-string-search "Mac" (getvar "platform")))) (c:txtexp))
(command "_layer" "set" "nitride" "")
(command "_layer" "set" "text" "")
(command-s "_text" "4448.865,963.3" "2" "-90" "nominal: 150" )
(sssetfirst nil (ssget "_L"))
(if (not (numberp (vl-string-search "Mac" (getvar "platform")))) (c:txtexp))
(command "_layer" "set" "nitride" "")
(command "_layer" "set" "indicators" "")
(setq coords (list 
(list 4400.415 940) 
(list 4400.415 920) 
(list 4380.415 900) 
(list 4400.415 880) 
(list 4400.415 860) 
(list 4400.415 900) 
(list 4400.415 887.0711) 
(list 4387.4861 900) 
(list 4400.415 912.9289) 
(list 4400.415 900)))
(apply 'command (append '("pline") coords '("c")))
(command "._fillet" "radius" "1" "._fillet" "P" (entlast))
(setq coords (list 
(list 4559.585 940) 
(list 4559.585 920) 
(list 4579.585 900) 
(list 4559.585 880) 
(list 4559.585 860) 
(list 4559.585 900) 
(list 4559.585 887.0711) 
(list 4572.5139 900) 
(list 4559.585 912.9289) 
(list 4559.585 900)))
(apply 'command (append '("pline") coords '("c")))
(command "._fillet" "radius" "1" "._fillet" "P" (entlast))
(command "_layer" "set" "holes" "")
(command "_circle" "4398.0629,914.1124" "0.5")
(command "_circle" "4395.7109,911.7603" "0.5")
(command "_circle" "4393.3588,909.4083" "0.5")
(command "_circle" "4391.0067,907.0562" "0.5")
(command "_circle" "4388.6547,904.7041" "0.5")
(command "_circle" "4386.3026,902.3521" "0.5")
(command "_circle" "4383.9505,900" "0.5")
(command "_circle" "4386.3026,897.6479" "0.5")
(command "_circle" "4388.6547,895.2959" "0.5")
(command "_circle" "4391.0067,892.9438" "0.5")
(command "_circle" "4393.3588,890.5917" "0.5")
(command "_circle" "4395.7109,888.2397" "0.5")
(command "_circle" "4398.0629,885.8876" "0.5")
(command "_circle" "4561.9371,914.1124" "0.5")
(command "_circle" "4564.2891,911.7603" "0.5")
(command "_circle" "4566.6412,909.4083" "0.5")
(command "_circle" "4568.9933,907.0562" "0.5")
(command "_circle" "4571.3453,904.7041" "0.5")
(command "_circle" "4573.6974,902.3521" "0.5")
(command "_circle" "4576.0495,900" "0.5")
(command "_circle" "4573.6974,897.6479" "0.5")
(command "_circle" "4571.3453,895.2959" "0.5")
(command "_circle" "4568.9933,892.9438" "0.5")
(command "_circle" "4566.6412,890.5917" "0.5")
(command "_circle" "4564.2891,888.2397" "0.5")
(command "_circle" "4561.9371,885.8876" "0.5")
(command "_layer" "set" "nitride" "")
(command "_block" "blkcoupler14" "4480,900" coupler14 "")
(command "_insert" "blkcoupler14" "4480,900" "1" "1" "0")
(command "_insert" "blkcoupler14" "4480,900" "1" "1" "180")
(command "_block" "blksinglenanobeam14" "4480,900" singlenanobeam14 "")
(command "_insert" "blksinglenanobeam14" "4480,900" "1" "1" "0")
(command "_insert" "blksinglenanobeam14" "4480,900" "1" "1" "180")
(command "_block" "blkanglednodearray14" "4480,900" anglednodearray14 "")
(command "_insert" "blkanglednodearray14" "4480,900" "1" "1" "0")
(command "_insert" "blkanglednodearray14" "4480,900" "1" "1" "180")
(command "_block" "blkcooledsinglenanobeam14" "4480,900" cooledsinglenanobeam14 "")
(command "_insert" "blkcooledsinglenanobeam14" "4480,900" "1" "1" "0")
(command "_insert" "blkcooledsinglenanobeam14" "4480,900" "1" "1" "180")
(command "_block" "blkyjunction14" "4480,900" yjunction14 "")
(command "_insert" "blkyjunction14" "4480,900" "1" "1" "0")
(command "_insert" "blkyjunction14" "4480,900" "1" "1" "180")
; DRAWING BULGING VEE GROOVE
(command "_layer" "set" "vgroove" "")
(setq coords (list 
(list 4405.415 -605) 
(list 4405.415 0) 
(list 4405.415 0) 
(list 4405.415 1800) 
(list 4405.415 1800) 
(list 4405.415 2405) 
(list 4554.585 2405) 
(list 4554.585 1800) 
(list 4554.585 1800) 
(list 4554.585 0) 
(list 4554.585 0) 
(list 4554.585 -605)))
(apply 'command (append '("pline") coords '("c")))
(command "._fillet" "radius" "0" "._fillet" "P" (entlast))
(command "_layer" "set" "window" "")
(command "_rectangle" "4405.415,-1935" "4554.585,-600")
(command "_rectangle" "4405.415,2400" "4554.585,5300")
(command "_layer" "set" "grid" "")
(command "_rectangle" "4406.415,-1934" "4429.9433,-1909.2133")
(command "_array" "last" "" "R" "75" "3" "25.7867" "24.5283")
(command "_rectangle" "4481,-1934" "4504.5283,-1909.2133")
(command "_array" "last" "" "R" "75" "3" "25.7867" "24.5283")
(command "_rectangle" "4406.415,1" "4429.9433,25.7")
(command "_array" "last" "" "R" "70" "3" "25.7" "24.5283")
(command "_rectangle" "4481,1" "4504.5283,25.7")
(command "_array" "last" "" "R" "70" "3" "25.7" "24.5283")
(command "_rectangle" "4406.415,1801" "4429.9433,1825.9185")
(command "_array" "last" "" "R" "135" "3" "25.9185" "24.5283")
(command "_rectangle" "4481,1801" "4504.5283,1825.9185")
(command "_array" "last" "" "R" "135" "3" "25.9185" "24.5283")
(command "_layer" "set" "vgrooveFDA" "")
(command "_rectangle" "4554.585,-2233" "4405.415,-1933")
(command "_layer" "set" "nitride" "")
(command "_layer" "set" "holes" "")
(command "_circle" "4557.085,331.5" "0.5")
(command "_array" "last" "" "R" "379" "1" "3" "2.5")
(command "_circle" "4402.915,331.5" "0.5")
(command "_array" "last" "" "R" "379" "1" "3" "-2.5")
(command "_layer" "set" "nitride" "")
(command "_layer" "set" "window" "")
(command "_layer" "set" "window" "")
(command "_rectangle" "4559.585,0" "4720.415,1800")
(command "._fillet" "radius" "20" "._fillet" "P" (entlast))
(command "_layer" "set" "grid" "")
(command "_rectangle" "4560.585,1" "4582.4179,25.7")
(command "_array" "last" "" "R" "70" "7" "25.7" "22.8329")
(command "_layer" "set" "nitride" "")
; DRAWING REGION LAYER
(command "_layer" "set" "regionLayer14" "")
(command "_rectangle" "4400,-460" "4560,2260")
(command "_layer" "set" "nitride" "")
(setq coupler14 nil)
(setq singlenanobeam14 nil)
(setq anglednodearray14 nil)
(setq cooledsinglenanobeam14 nil)
(setq yjunction14 nil)
; DEVICE #15
(command "_layer" "set" "window" "")
(command "_circle" "4712.915,-415" "5")
(command "_circle" "4712.915,-402.5" "5")
(command "_circle" "4712.915,-390" "5")
(command "_circle" "4712.915,-377.5" "5")
(command "_circle" "4700.415,-415" "5")
(command "_circle" "4700.415,-402.5" "5")
(command "_circle" "4700.415,-390" "5")
(command "_circle" "4700.415,-377.5" "5")
(command "_circle" "4687.915,-415" "5")
(command "_circle" "4687.915,-402.5" "5")
(command "_circle" "4687.915,-390" "5")
(command "_circle" "4687.915,-377.5" "5")
(command "_circle" "4675.415,-415" "5")
(command "_circle" "4675.415,-402.5" "5")
(command "_circle" "4675.415,-390" "5")
(command "_layer" "set" "nitride" "")
(setq currobj nil)
(setq currobj (ssadd))
; DRAWING COUPLER
(setq coords (list 
(list 4800.0645 -415) 
(list 4800.0645 -413) 
(list 4873.585 -413) 
(list 4873.585 -413) 
(list 4873.9677 -413.0761) 
(list 4874.2921 -413.2929) 
(list 4874.5089 -413.6173) 
(list 4874.585 -414) 
(list 4874.585 -411.8) 
(list 4874.585 -411.8) 
(list 4874.5089 -412.1827) 
(list 4874.2921 -412.5071) 
(list 4873.9677 -412.7239) 
(list 4873.585 -412.8) 
(list 4800.0645 -412.8) 
(list 4800.0645 -410.8) 
(list 4799.9355 -410.8) 
(list 4799.9355 -412.8) 
(list 4726.415 -412.8) 
(list 4726.0323 -412.7239) 
(list 4725.7079 -412.5071) 
(list 4725.4911 -412.1827) 
(list 4725.415 -411.8) 
(list 4725.415 -411.8) 
(list 4725.415 -414) 
(list 4725.4911 -413.6173) 
(list 4725.7079 -413.2929) 
(list 4726.0323 -413.0761) 
(list 4726.415 -413) 
(list 4726.415 -413) 
(list 4799.9355 -413) 
(list 4799.9355 -415)))
(apply 'command (append '("pline") coords '("c")))
(setq currobj (ssadd (entlast) currobj))
(command "._fillet" "radius" "0.3" "._fillet" "P" (entlast))
(command "_layer" "set" "holes" "")
(command "_circle" "4800,-412.9" "0.113")
(setq currobj (ssadd (entlast) currobj))
(command "_layer" "set" "nitride" "")
(command "_layer" "set" "text" "")
(command "_circle" "4799.2,-415" "0.075")
(command "_circle" "4799.2,-414.7" "0.075")
(command "_circle" "4799.2,-414.4" "0.075")
(command "_circle" "4798.9,-415" "0.075")
(command "_circle" "4798.9,-414.7" "0.075")
(command "_circle" "4798.9,-414.4" "0.075")
(command "_circle" "4798.6,-415" "0.075")
(command "_circle" "4798.6,-414.7" "0.075")
(command "_circle" "4798.6,-414.4" "0.075")
(command "_layer" "set" "nitride" "")
(command "_layer" "set" "prebias" "")
(command "_rectangle" "4725.415,-414" "4874.585,-411.8")
(setq currobj (ssadd (entlast) currobj))
(command "_rectangle" "4799.9355,-415" "4800.0645,-410.8")
(setq currobj (ssadd (entlast) currobj))
(command "_layer" "set" "nitride" "")
(setq coupler15 currobj)
(setq currobj nil)
(setq currobj (ssadd))
; DRAWING SINGLE NANOBEAM
(setq coords (list 
(list 4800.0645 -410.8) 
(list 4800.0645 -409.1417) 
(list 4800.0645 -407.4833) 
(list 4800.0645 -405.825) 
(list 4800.0645 -404.1667) 
(list 4800.0645 -402.5083) 
(list 4800.0645 -400.85) 
(list 4800.0645 -399.1917) 
(list 4800.0645 -397.5333) 
(list 4800.0646 -395.875) 
(list 4800.0646 -394.2167) 
(list 4800.0646 -392.5583) 
(list 4800.0646 -390.9) 
(list 4800.0647 -389.2417) 
(list 4800.0647 -387.5833) 
(list 4800.0647 -385.925) 
(list 4800.0648 -384.2667) 
(list 4800.0648 -382.6083) 
(list 4800.0649 -380.95) 
(list 4800.065 -379.2917) 
(list 4800.0651 -377.6333) 
(list 4800.0651 -375.975) 
(list 4800.0652 -374.3167) 
(list 4800.0653 -372.6583) 
(list 4800.0655 -371) 
(list 4800.0656 -369.3417) 
(list 4800.0657 -367.6833) 
(list 4800.0659 -366.025) 
(list 4800.066 -364.3667) 
(list 4800.0662 -362.7083) 
(list 4800.0664 -361.05) 
(list 4800.0666 -359.3917) 
(list 4800.0668 -357.7333) 
(list 4800.067 -356.075) 
(list 4800.0672 -354.4167) 
(list 4800.0675 -352.7583) 
(list 4800.0678 -351.1) 
(list 4800.068 -349.4417) 
(list 4800.0683 -347.7833) 
(list 4800.0686 -346.125) 
(list 4800.069 -344.4667) 
(list 4800.0693 -342.8083) 
(list 4800.0697 -341.15) 
(list 4800.07 -339.4917) 
(list 4800.0704 -337.8333) 
(list 4800.0709 -336.175) 
(list 4800.0713 -334.5167) 
(list 4800.0717 -332.8583) 
(list 4800.0722 -331.2) 
(list 4800.0727 -329.5417) 
(list 4800.0732 -327.8833) 
(list 4800.0737 -326.225) 
(list 4800.0743 -324.5667) 
(list 4800.0749 -322.9083) 
(list 4800.0755 -321.25) 
(list 4800.0761 -319.5917) 
(list 4800.0767 -317.9333) 
(list 4800.0774 -316.275) 
(list 4800.0781 -314.6167) 
(list 4800.0788 -312.9583) 
(list 4800.0796 -311.3) 
(list 4800.0803 -309.6417) 
(list 4800.0811 -307.9833) 
(list 4800.0819 -306.325) 
(list 4800.0828 -304.6667) 
(list 4800.0837 -303.0083) 
(list 4800.0845 -301.35) 
(list 4800.0855 -299.6917) 
(list 4800.0864 -298.0333) 
(list 4800.0874 -296.375) 
(list 4800.0884 -294.7167) 
(list 4800.0895 -293.0583) 
(list 4800.0905 -291.4) 
(list 4800.0916 -289.7417) 
(list 4800.0928 -288.0833) 
(list 4800.0939 -286.425) 
(list 4800.0951 -284.7667) 
(list 4800.0963 -283.1083) 
(list 4800.0976 -281.45) 
(list 4800.0989 -279.7917) 
(list 4800.1002 -278.1333) 
(list 4800.1016 -276.475) 
(list 4800.1029 -274.8167) 
(list 4800.1044 -273.1583) 
(list 4800.1058 -271.5) 
(list 4800.1073 -269.8417) 
(list 4800.1089 -268.1833) 
(list 4800.1104 -266.525) 
(list 4800.112 -264.8667) 
(list 4800.1137 -263.2083) 
(list 4800.1153 -261.55) 
(list 4800.117 -259.8917) 
(list 4800.1188 -258.2333) 
(list 4800.1206 -256.575) 
(list 4800.1224 -254.9167) 
(list 4800.1243 -253.2583) 
(list 4800.1262 -251.6) 
(list 4800.1281 -249.9417) 
(list 4800.1301 -248.2833) 
(list 4800.1322 -246.625) 
(list 4800.1342 -244.9667) 
(list 4800.1363 -243.3083) 
(list 4800.1385 -241.65) 
(list 4800.1407 -239.9917) 
(list 4800.1429 -238.3333) 
(list 4800.1452 -236.675) 
(list 4800.1476 -235.0167) 
(list 4800.1499 -233.3583) 
(list 4800.1523 -231.7) 
(list 4800.1548 -230.0417) 
(list 4800.1573 -228.3833) 
(list 4800.1599 -226.725) 
(list 4800.1625 -225.0667) 
(list 4800.1651 -223.4083) 
(list 4800.1678 -221.75) 
(list 4800.1706 -220.0917) 
(list 4800.1733 -218.4333) 
(list 4800.1762 -216.775) 
(list 4800.1791 -215.1167) 
(list 4800.182 -213.4583) 
(list 4800.185 -211.8) 
(list 4799.815 -211.8) 
(list 4799.818 -213.4583) 
(list 4799.8209 -215.1167) 
(list 4799.8238 -216.775) 
(list 4799.8267 -218.4333) 
(list 4799.8294 -220.0917) 
(list 4799.8322 -221.75) 
(list 4799.8349 -223.4083) 
(list 4799.8375 -225.0667) 
(list 4799.8401 -226.725) 
(list 4799.8427 -228.3833) 
(list 4799.8452 -230.0417) 
(list 4799.8477 -231.7) 
(list 4799.8501 -233.3583) 
(list 4799.8524 -235.0167) 
(list 4799.8548 -236.675) 
(list 4799.8571 -238.3333) 
(list 4799.8593 -239.9917) 
(list 4799.8615 -241.65) 
(list 4799.8637 -243.3083) 
(list 4799.8658 -244.9667) 
(list 4799.8678 -246.625) 
(list 4799.8699 -248.2833) 
(list 4799.8719 -249.9417) 
(list 4799.8738 -251.6) 
(list 4799.8757 -253.2583) 
(list 4799.8776 -254.9167) 
(list 4799.8794 -256.575) 
(list 4799.8812 -258.2333) 
(list 4799.883 -259.8917) 
(list 4799.8847 -261.55) 
(list 4799.8863 -263.2083) 
(list 4799.888 -264.8667) 
(list 4799.8896 -266.525) 
(list 4799.8911 -268.1833) 
(list 4799.8927 -269.8417) 
(list 4799.8942 -271.5) 
(list 4799.8956 -273.1583) 
(list 4799.8971 -274.8167) 
(list 4799.8984 -276.475) 
(list 4799.8998 -278.1333) 
(list 4799.9011 -279.7917) 
(list 4799.9024 -281.45) 
(list 4799.9037 -283.1083) 
(list 4799.9049 -284.7667) 
(list 4799.9061 -286.425) 
(list 4799.9072 -288.0833) 
(list 4799.9084 -289.7417) 
(list 4799.9095 -291.4) 
(list 4799.9105 -293.0583) 
(list 4799.9116 -294.7167) 
(list 4799.9126 -296.375) 
(list 4799.9136 -298.0333) 
(list 4799.9145 -299.6917) 
(list 4799.9155 -301.35) 
(list 4799.9163 -303.0083) 
(list 4799.9172 -304.6667) 
(list 4799.9181 -306.325) 
(list 4799.9189 -307.9833) 
(list 4799.9197 -309.6417) 
(list 4799.9204 -311.3) 
(list 4799.9212 -312.9583) 
(list 4799.9219 -314.6167) 
(list 4799.9226 -316.275) 
(list 4799.9233 -317.9333) 
(list 4799.9239 -319.5917) 
(list 4799.9245 -321.25) 
(list 4799.9251 -322.9083) 
(list 4799.9257 -324.5667) 
(list 4799.9263 -326.225) 
(list 4799.9268 -327.8833) 
(list 4799.9273 -329.5417) 
(list 4799.9278 -331.2) 
(list 4799.9283 -332.8583) 
(list 4799.9287 -334.5167) 
(list 4799.9291 -336.175) 
(list 4799.9296 -337.8333) 
(list 4799.93 -339.4917) 
(list 4799.9303 -341.15) 
(list 4799.9307 -342.8083) 
(list 4799.931 -344.4667) 
(list 4799.9314 -346.125) 
(list 4799.9317 -347.7833) 
(list 4799.932 -349.4417) 
(list 4799.9322 -351.1) 
(list 4799.9325 -352.7583) 
(list 4799.9328 -354.4167) 
(list 4799.933 -356.075) 
(list 4799.9332 -357.7333) 
(list 4799.9334 -359.3917) 
(list 4799.9336 -361.05) 
(list 4799.9338 -362.7083) 
(list 4799.934 -364.3667) 
(list 4799.9341 -366.025) 
(list 4799.9343 -367.6833) 
(list 4799.9344 -369.3417) 
(list 4799.9345 -371) 
(list 4799.9347 -372.6583) 
(list 4799.9348 -374.3167) 
(list 4799.9349 -375.975) 
(list 4799.9349 -377.6333) 
(list 4799.935 -379.2917) 
(list 4799.9351 -380.95) 
(list 4799.9352 -382.6083) 
(list 4799.9352 -384.2667) 
(list 4799.9353 -385.925) 
(list 4799.9353 -387.5833) 
(list 4799.9353 -389.2417) 
(list 4799.9354 -390.9) 
(list 4799.9354 -392.5583) 
(list 4799.9354 -394.2167) 
(list 4799.9354 -395.875) 
(list 4799.9355 -397.5333) 
(list 4799.9355 -399.1917) 
(list 4799.9355 -400.85) 
(list 4799.9355 -402.5083) 
(list 4799.9355 -404.1667) 
(list 4799.9355 -405.825) 
(list 4799.9355 -407.4833) 
(list 4799.9355 -409.1417) 
(list 4799.9355 -410.8)))
(apply 'command (append '("pline") coords '("c")))
(setq currobj (ssadd (entlast) currobj))
(command "_layer" "set" "prebias" "")
(command "_rectangle" "4799.815,-410.8" "4800.185,-211.8")
(setq currobj (ssadd (entlast) currobj))
(command "_layer" "set" "nitride" "")
(setq singlenanobeam15 currobj)
(setq currobj nil)
(setq currobj (ssadd))
; DRAWING NODE ARRAY
(setq coords (list 
(list 4800.185 -211.8) 
(list 4800.5625 -201.8) 
(list 4800.5625 -201.8) 
(list 4800.5625 -200.8) 
(list 4874.585 -212.6864) 
(list 4874.585 -207.7434) 
(list 4800.5625 -197.357) 
(list 4800.5625 -196.357) 
(list 4800.5625 -196.357) 
(list 4800.2625 -186.357) 
(list 4799.7375 -186.357) 
(list 4799.4375 -196.357) 
(list 4799.4375 -196.357) 
(list 4799.4375 -197.357) 
(list 4725.415 -207.7434) 
(list 4725.415 -212.6864) 
(list 4799.4375 -200.8) 
(list 4799.4375 -201.8) 
(list 4799.4375 -201.8) 
(list 4799.815 -211.8)))
(apply 'command (append '("pline") coords '("c")))
(setq currobj (ssadd (entlast) currobj))
(command "_layer" "set" "prebias" "")
(setq coords (list 
(list 4799.4375 -212.6864) 
(list 4799.4375 -200.8) 
(list 4725.415 -212.6864) 
(list 4725.415 -207.7434) 
(list 4799.4375 -197.357) 
(list 4799.4375 -186.357) 
(list 4800.5625 -186.357) 
(list 4800.5625 -197.357) 
(list 4874.585 -207.7434) 
(list 4874.585 -212.6864) 
(list 4800.5625 -200.8) 
(list 4800.5625 -212.6864)))
(apply 'command (append '("pline") coords '("c")))
(setq currobj (ssadd (entlast) currobj))
(command "_layer" "set" "nitride" "")
(command "_layer" "set" "fda1" "")
(setq coords (list 
(list 4800.5625 -200.657) 
(list 4874.585 -212.5434) 
(list 4874.585 -212.3664) 
(list 4800.5625 -200.58)))
(apply 'command (append '("pline") coords '("c")))
(setq currobj (ssadd (entlast) currobj))
(setq coords (list 
(list 4800.5625 -200.437) 
(list 4874.585 -212.2234) 
(list 4874.585 -212.0464) 
(list 4800.5625 -200.36)))
(apply 'command (append '("pline") coords '("c")))
(setq currobj (ssadd (entlast) currobj))
(setq coords (list 
(list 4800.5625 -200.217) 
(list 4874.585 -211.9034) 
(list 4874.585 -211.7264) 
(list 4800.5625 -200.14)))
(apply 'command (append '("pline") coords '("c")))
(setq currobj (ssadd (entlast) currobj))
(setq coords (list 
(list 4800.5625 -199.997) 
(list 4874.585 -211.5834) 
(list 4874.585 -211.4064) 
(list 4800.5625 -199.92)))
(apply 'command (append '("pline") coords '("c")))
(setq currobj (ssadd (entlast) currobj))
(setq coords (list 
(list 4800.5625 -199.777) 
(list 4874.585 -211.2634) 
(list 4874.585 -211.0864) 
(list 4800.5625 -199.7)))
(apply 'command (append '("pline") coords '("c")))
(setq currobj (ssadd (entlast) currobj))
(setq coords (list 
(list 4800.5625 -199.557) 
(list 4874.585 -210.9434) 
(list 4874.585 -210.7664) 
(list 4800.5625 -199.48)))
(apply 'command (append '("pline") coords '("c")))
(setq currobj (ssadd (entlast) currobj))
(setq coords (list 
(list 4800.5625 -199.337) 
(list 4874.585 -210.6234) 
(list 4874.585 -210.4464) 
(list 4800.5625 -199.26)))
(apply 'command (append '("pline") coords '("c")))
(setq currobj (ssadd (entlast) currobj))
(setq coords (list 
(list 4800.5625 -199.117) 
(list 4874.585 -210.3034) 
(list 4874.585 -210.1264) 
(list 4800.5625 -199.04)))
(apply 'command (append '("pline") coords '("c")))
(setq currobj (ssadd (entlast) currobj))
(setq coords (list 
(list 4800.5625 -198.897) 
(list 4874.585 -209.9834) 
(list 4874.585 -209.8064) 
(list 4800.5625 -198.82)))
(apply 'command (append '("pline") coords '("c")))
(setq currobj (ssadd (entlast) currobj))
(setq coords (list 
(list 4800.5625 -198.677) 
(list 4874.585 -209.6634) 
(list 4874.585 -209.4864) 
(list 4800.5625 -198.6)))
(apply 'command (append '("pline") coords '("c")))
(setq currobj (ssadd (entlast) currobj))
(setq coords (list 
(list 4800.5625 -198.457) 
(list 4874.585 -209.3434) 
(list 4874.585 -209.1664) 
(list 4800.5625 -198.38)))
(apply 'command (append '("pline") coords '("c")))
(setq currobj (ssadd (entlast) currobj))
(setq coords (list 
(list 4800.5625 -198.237) 
(list 4874.585 -209.0234) 
(list 4874.585 -208.8464) 
(list 4800.5625 -198.16)))
(apply 'command (append '("pline") coords '("c")))
(setq currobj (ssadd (entlast) currobj))
(setq coords (list 
(list 4800.5625 -198.017) 
(list 4874.585 -208.7034) 
(list 4874.585 -208.5264) 
(list 4800.5625 -197.94)))
(apply 'command (append '("pline") coords '("c")))
(setq currobj (ssadd (entlast) currobj))
(setq coords (list 
(list 4800.5625 -197.797) 
(list 4874.585 -208.3834) 
(list 4874.585 -208.2064) 
(list 4800.5625 -197.72)))
(apply 'command (append '("pline") coords '("c")))
(setq currobj (ssadd (entlast) currobj))
(setq coords (list 
(list 4800.5625 -197.577) 
(list 4874.585 -208.0634) 
(list 4874.585 -207.8864) 
(list 4800.5625 -197.5)))
(apply 'command (append '("pline") coords '("c")))
(setq currobj (ssadd (entlast) currobj))
(setq coords (list 
(list 4799.4375 -197.5) 
(list 4725.415 -207.8864) 
(list 4725.415 -208.0634) 
(list 4799.4375 -197.577)))
(apply 'command (append '("pline") coords '("c")))
(setq currobj (ssadd (entlast) currobj))
(setq coords (list 
(list 4799.4375 -197.72) 
(list 4725.415 -208.2064) 
(list 4725.415 -208.3834) 
(list 4799.4375 -197.797)))
(apply 'command (append '("pline") coords '("c")))
(setq currobj (ssadd (entlast) currobj))
(setq coords (list 
(list 4799.4375 -197.94) 
(list 4725.415 -208.5264) 
(list 4725.415 -208.7034) 
(list 4799.4375 -198.017)))
(apply 'command (append '("pline") coords '("c")))
(setq currobj (ssadd (entlast) currobj))
(setq coords (list 
(list 4799.4375 -198.16) 
(list 4725.415 -208.8464) 
(list 4725.415 -209.0234) 
(list 4799.4375 -198.237)))
(apply 'command (append '("pline") coords '("c")))
(setq currobj (ssadd (entlast) currobj))
(setq coords (list 
(list 4799.4375 -198.38) 
(list 4725.415 -209.1664) 
(list 4725.415 -209.3434) 
(list 4799.4375 -198.457)))
(apply 'command (append '("pline") coords '("c")))
(setq currobj (ssadd (entlast) currobj))
(setq coords (list 
(list 4799.4375 -198.6) 
(list 4725.415 -209.4864) 
(list 4725.415 -209.6634) 
(list 4799.4375 -198.677)))
(apply 'command (append '("pline") coords '("c")))
(setq currobj (ssadd (entlast) currobj))
(setq coords (list 
(list 4799.4375 -198.82) 
(list 4725.415 -209.8064) 
(list 4725.415 -209.9834) 
(list 4799.4375 -198.897)))
(apply 'command (append '("pline") coords '("c")))
(setq currobj (ssadd (entlast) currobj))
(setq coords (list 
(list 4799.4375 -199.04) 
(list 4725.415 -210.1264) 
(list 4725.415 -210.3034) 
(list 4799.4375 -199.117)))
(apply 'command (append '("pline") coords '("c")))
(setq currobj (ssadd (entlast) currobj))
(setq coords (list 
(list 4799.4375 -199.26) 
(list 4725.415 -210.4464) 
(list 4725.415 -210.6234) 
(list 4799.4375 -199.337)))
(apply 'command (append '("pline") coords '("c")))
(setq currobj (ssadd (entlast) currobj))
(setq coords (list 
(list 4799.4375 -199.48) 
(list 4725.415 -210.7664) 
(list 4725.415 -210.9434) 
(list 4799.4375 -199.557)))
(apply 'command (append '("pline") coords '("c")))
(setq currobj (ssadd (entlast) currobj))
(setq coords (list 
(list 4799.4375 -199.7) 
(list 4725.415 -211.0864) 
(list 4725.415 -211.2634) 
(list 4799.4375 -199.777)))
(apply 'command (append '("pline") coords '("c")))
(setq currobj (ssadd (entlast) currobj))
(setq coords (list 
(list 4799.4375 -199.92) 
(list 4725.415 -211.4064) 
(list 4725.415 -211.5834) 
(list 4799.4375 -199.997)))
(apply 'command (append '("pline") coords '("c")))
(setq currobj (ssadd (entlast) currobj))
(setq coords (list 
(list 4799.4375 -200.14) 
(list 4725.415 -211.7264) 
(list 4725.415 -211.9034) 
(list 4799.4375 -200.217)))
(apply 'command (append '("pline") coords '("c")))
(setq currobj (ssadd (entlast) currobj))
(setq coords (list 
(list 4799.4375 -200.36) 
(list 4725.415 -212.0464) 
(list 4725.415 -212.2234) 
(list 4799.4375 -200.437)))
(apply 'command (append '("pline") coords '("c")))
(setq currobj (ssadd (entlast) currobj))
(setq coords (list 
(list 4799.4375 -200.58) 
(list 4725.415 -212.3664) 
(list 4725.415 -212.5434) 
(list 4799.4375 -200.657)))
(apply 'command (append '("pline") coords '("c")))
(setq currobj (ssadd (entlast) currobj))
(command "_layer" "set" "nitride" "")
(command "_layer" "set" "text" "")
(command "_circle" "4798.985,-211.8" "0.075")
(command "_circle" "4798.985,-211.5" "0.075")
(command "_circle" "4798.985,-211.2" "0.075")
(command "_circle" "4798.985,-210.9" "0.075")
(command "_circle" "4798.985,-210.6" "0.075")
(command "_circle" "4798.685,-211.8" "0.075")
(command "_circle" "4798.685,-211.5" "0.075")
(command "_circle" "4798.685,-211.2" "0.075")
(command "_circle" "4798.685,-210.9" "0.075")
(command "_circle" "4798.685,-210.6" "0.075")
(command "_circle" "4798.385,-211.8" "0.075")
(command "_circle" "4798.385,-211.5" "0.075")
(command "_circle" "4798.385,-211.2" "0.075")
(command "_circle" "4798.385,-210.9" "0.075")
(command "_circle" "4798.385,-210.6" "0.075")
(command "_circle" "4798.085,-211.8" "0.075")
(command "_circle" "4798.085,-211.5" "0.075")
(command "_circle" "4798.085,-211.2" "0.075")
(command "_circle" "4798.085,-210.9" "0.075")
(command "_circle" "4798.085,-210.6" "0.075")
(command "_circle" "4797.785,-211.8" "0.075")
(command "_circle" "4797.785,-211.5" "0.075")
(command "_circle" "4797.785,-211.2" "0.075")
(command "_circle" "4797.785,-210.9" "0.075")
(command "_circle" "4797.785,-210.6" "0.075")
(command "_layer" "set" "nitride" "")
(setq anglednodearray15 currobj)
(setq currobj nil)
(setq currobj (ssadd))
; DRAWING COOLED SINGLE NANOBEAM
(setq coords (list 
(list 4800.2625 -186.357) 
(list 4800.2625 -181.357) 
(list 4799.7375 -181.357) 
(list 4799.7375 -186.357)))
(apply 'command (append '("pline") coords '("c")))
(setq currobj (ssadd (entlast) currobj))
(command "_layer" "set" "prebias" "")
(command "_rectangle" "4799.7375,-186.357" "4800.2625,-181.357")
(setq currobj (ssadd (entlast) currobj))
(command "_layer" "set" "nitride" "")
(setq coords (list 
(list 4800.2625 -181.357) 
(list 4800.5625 -171.357) 
(list 4800.5625 -171.357) 
(list 4800.5625 -170.357) 
(list 4874.585 -171.107) 
(list 4874.585 -166.164) 
(list 4800.5625 -166.914) 
(list 4800.5625 -165.914) 
(list 4800.5625 -165.914) 
(list 4800.2625 -155.914) 
(list 4799.7375 -155.914) 
(list 4799.4375 -165.914) 
(list 4799.4375 -165.914) 
(list 4799.4375 -166.914) 
(list 4725.415 -166.164) 
(list 4725.415 -171.107) 
(list 4799.4375 -170.357) 
(list 4799.4375 -171.357) 
(list 4799.4375 -171.357) 
(list 4799.7375 -181.357)))
(apply 'command (append '("pline") coords '("c")))
(setq currobj (ssadd (entlast) currobj))
(command "_layer" "set" "prebias" "")
(setq coords (list 
(list 4799.4375 -181.357) 
(list 4799.4375 -170.357) 
(list 4725.415 -171.107) 
(list 4725.415 -166.164) 
(list 4799.4375 -166.914) 
(list 4799.4375 -155.914) 
(list 4800.5625 -155.914) 
(list 4800.5625 -166.914) 
(list 4874.585 -166.164) 
(list 4874.585 -171.107) 
(list 4800.5625 -170.357) 
(list 4800.5625 -181.357)))
(apply 'command (append '("pline") coords '("c")))
(setq currobj (ssadd (entlast) currobj))
(command "_layer" "set" "nitride" "")
(command "_layer" "set" "fda1" "")
(setq coords (list 
(list 4800.5625 -170.214) 
(list 4874.585 -170.964) 
(list 4874.585 -170.787) 
(list 4800.5625 -170.137)))
(apply 'command (append '("pline") coords '("c")))
(setq currobj (ssadd (entlast) currobj))
(setq coords (list 
(list 4800.5625 -169.994) 
(list 4874.585 -170.644) 
(list 4874.585 -170.467) 
(list 4800.5625 -169.917)))
(apply 'command (append '("pline") coords '("c")))
(setq currobj (ssadd (entlast) currobj))
(setq coords (list 
(list 4800.5625 -169.774) 
(list 4874.585 -170.324) 
(list 4874.585 -170.147) 
(list 4800.5625 -169.697)))
(apply 'command (append '("pline") coords '("c")))
(setq currobj (ssadd (entlast) currobj))
(setq coords (list 
(list 4800.5625 -169.554) 
(list 4874.585 -170.004) 
(list 4874.585 -169.827) 
(list 4800.5625 -169.477)))
(apply 'command (append '("pline") coords '("c")))
(setq currobj (ssadd (entlast) currobj))
(setq coords (list 
(list 4800.5625 -169.334) 
(list 4874.585 -169.684) 
(list 4874.585 -169.507) 
(list 4800.5625 -169.257)))
(apply 'command (append '("pline") coords '("c")))
(setq currobj (ssadd (entlast) currobj))
(setq coords (list 
(list 4800.5625 -169.114) 
(list 4874.585 -169.364) 
(list 4874.585 -169.187) 
(list 4800.5625 -169.037)))
(apply 'command (append '("pline") coords '("c")))
(setq currobj (ssadd (entlast) currobj))
(setq coords (list 
(list 4800.5625 -168.894) 
(list 4874.585 -169.044) 
(list 4874.585 -168.867) 
(list 4800.5625 -168.817)))
(apply 'command (append '("pline") coords '("c")))
(setq currobj (ssadd (entlast) currobj))
(setq coords (list 
(list 4800.5625 -168.674) 
(list 4874.585 -168.724) 
(list 4874.585 -168.547) 
(list 4800.5625 -168.597)))
(apply 'command (append '("pline") coords '("c")))
(setq currobj (ssadd (entlast) currobj))
(setq coords (list 
(list 4800.5625 -168.454) 
(list 4874.585 -168.404) 
(list 4874.585 -168.227) 
(list 4800.5625 -168.377)))
(apply 'command (append '("pline") coords '("c")))
(setq currobj (ssadd (entlast) currobj))
(setq coords (list 
(list 4800.5625 -168.234) 
(list 4874.585 -168.084) 
(list 4874.585 -167.907) 
(list 4800.5625 -168.157)))
(apply 'command (append '("pline") coords '("c")))
(setq currobj (ssadd (entlast) currobj))
(setq coords (list 
(list 4800.5625 -168.014) 
(list 4874.585 -167.764) 
(list 4874.585 -167.587) 
(list 4800.5625 -167.937)))
(apply 'command (append '("pline") coords '("c")))
(setq currobj (ssadd (entlast) currobj))
(setq coords (list 
(list 4800.5625 -167.794) 
(list 4874.585 -167.444) 
(list 4874.585 -167.267) 
(list 4800.5625 -167.717)))
(apply 'command (append '("pline") coords '("c")))
(setq currobj (ssadd (entlast) currobj))
(setq coords (list 
(list 4800.5625 -167.574) 
(list 4874.585 -167.124) 
(list 4874.585 -166.947) 
(list 4800.5625 -167.497)))
(apply 'command (append '("pline") coords '("c")))
(setq currobj (ssadd (entlast) currobj))
(setq coords (list 
(list 4800.5625 -167.354) 
(list 4874.585 -166.804) 
(list 4874.585 -166.627) 
(list 4800.5625 -167.277)))
(apply 'command (append '("pline") coords '("c")))
(setq currobj (ssadd (entlast) currobj))
(setq coords (list 
(list 4800.5625 -167.134) 
(list 4874.585 -166.484) 
(list 4874.585 -166.307) 
(list 4800.5625 -167.057)))
(apply 'command (append '("pline") coords '("c")))
(setq currobj (ssadd (entlast) currobj))
(setq coords (list 
(list 4799.4375 -167.057) 
(list 4725.415 -166.307) 
(list 4725.415 -166.484) 
(list 4799.4375 -167.134)))
(apply 'command (append '("pline") coords '("c")))
(setq currobj (ssadd (entlast) currobj))
(setq coords (list 
(list 4799.4375 -167.277) 
(list 4725.415 -166.627) 
(list 4725.415 -166.804) 
(list 4799.4375 -167.354)))
(apply 'command (append '("pline") coords '("c")))
(setq currobj (ssadd (entlast) currobj))
(setq coords (list 
(list 4799.4375 -167.497) 
(list 4725.415 -166.947) 
(list 4725.415 -167.124) 
(list 4799.4375 -167.574)))
(apply 'command (append '("pline") coords '("c")))
(setq currobj (ssadd (entlast) currobj))
(setq coords (list 
(list 4799.4375 -167.717) 
(list 4725.415 -167.267) 
(list 4725.415 -167.444) 
(list 4799.4375 -167.794)))
(apply 'command (append '("pline") coords '("c")))
(setq currobj (ssadd (entlast) currobj))
(setq coords (list 
(list 4799.4375 -167.937) 
(list 4725.415 -167.587) 
(list 4725.415 -167.764) 
(list 4799.4375 -168.014)))
(apply 'command (append '("pline") coords '("c")))
(setq currobj (ssadd (entlast) currobj))
(setq coords (list 
(list 4799.4375 -168.157) 
(list 4725.415 -167.907) 
(list 4725.415 -168.084) 
(list 4799.4375 -168.234)))
(apply 'command (append '("pline") coords '("c")))
(setq currobj (ssadd (entlast) currobj))
(setq coords (list 
(list 4799.4375 -168.377) 
(list 4725.415 -168.227) 
(list 4725.415 -168.404) 
(list 4799.4375 -168.454)))
(apply 'command (append '("pline") coords '("c")))
(setq currobj (ssadd (entlast) currobj))
(setq coords (list 
(list 4799.4375 -168.597) 
(list 4725.415 -168.547) 
(list 4725.415 -168.724) 
(list 4799.4375 -168.674)))
(apply 'command (append '("pline") coords '("c")))
(setq currobj (ssadd (entlast) currobj))
(setq coords (list 
(list 4799.4375 -168.817) 
(list 4725.415 -168.867) 
(list 4725.415 -169.044) 
(list 4799.4375 -168.894)))
(apply 'command (append '("pline") coords '("c")))
(setq currobj (ssadd (entlast) currobj))
(setq coords (list 
(list 4799.4375 -169.037) 
(list 4725.415 -169.187) 
(list 4725.415 -169.364) 
(list 4799.4375 -169.114)))
(apply 'command (append '("pline") coords '("c")))
(setq currobj (ssadd (entlast) currobj))
(setq coords (list 
(list 4799.4375 -169.257) 
(list 4725.415 -169.507) 
(list 4725.415 -169.684) 
(list 4799.4375 -169.334)))
(apply 'command (append '("pline") coords '("c")))
(setq currobj (ssadd (entlast) currobj))
(setq coords (list 
(list 4799.4375 -169.477) 
(list 4725.415 -169.827) 
(list 4725.415 -170.004) 
(list 4799.4375 -169.554)))
(apply 'command (append '("pline") coords '("c")))
(setq currobj (ssadd (entlast) currobj))
(setq coords (list 
(list 4799.4375 -169.697) 
(list 4725.415 -170.147) 
(list 4725.415 -170.324) 
(list 4799.4375 -169.774)))
(apply 'command (append '("pline") coords '("c")))
(setq currobj (ssadd (entlast) currobj))
(setq coords (list 
(list 4799.4375 -169.917) 
(list 4725.415 -170.467) 
(list 4725.415 -170.644) 
(list 4799.4375 -169.994)))
(apply 'command (append '("pline") coords '("c")))
(setq currobj (ssadd (entlast) currobj))
(setq coords (list 
(list 4799.4375 -170.137) 
(list 4725.415 -170.787) 
(list 4725.415 -170.964) 
(list 4799.4375 -170.214)))
(apply 'command (append '("pline") coords '("c")))
(setq currobj (ssadd (entlast) currobj))
(command "_layer" "set" "nitride" "")
(command "_layer" "set" "text" "")
(command "_circle" "4799.0625,-181.357" "0.075")
(command "_circle" "4799.0625,-181.057" "0.075")
(command "_circle" "4799.0625,-180.757" "0.075")
(command "_circle" "4799.0625,-180.457" "0.075")
(command "_circle" "4799.0625,-180.157" "0.075")
(command "_circle" "4798.7625,-181.357" "0.075")
(command "_circle" "4798.7625,-181.057" "0.075")
(command "_circle" "4798.7625,-180.757" "0.075")
(command "_circle" "4798.7625,-180.457" "0.075")
(command "_circle" "4798.7625,-180.157" "0.075")
(command "_circle" "4798.4625,-181.357" "0.075")
(command "_circle" "4798.4625,-181.057" "0.075")
(command "_circle" "4798.4625,-180.757" "0.075")
(command "_circle" "4798.4625,-180.457" "0.075")
(command "_circle" "4798.4625,-180.157" "0.075")
(command "_circle" "4798.1625,-181.357" "0.075")
(command "_circle" "4798.1625,-181.057" "0.075")
(command "_circle" "4798.1625,-180.757" "0.075")
(command "_circle" "4798.1625,-180.457" "0.075")
(command "_circle" "4798.1625,-180.157" "0.075")
(command "_circle" "4797.8625,-181.357" "0.075")
(command "_circle" "4797.8625,-181.057" "0.075")
(command "_circle" "4797.8625,-180.757" "0.075")
(command "_circle" "4797.8625,-180.457" "0.075")
(command "_circle" "4797.8625,-180.157" "0.075")
(command "_layer" "set" "nitride" "")
(setq coords (list 
(list 4800.2625 -155.914) 
(list 4800.2625 -40.2693) 
(list 4799.7375 -40.2693) 
(list 4799.7375 -155.914)))
(apply 'command (append '("pline") coords '("c")))
(setq currobj (ssadd (entlast) currobj))
(command "_layer" "set" "prebias" "")
(command "_rectangle" "4799.7375,-155.914" "4800.2625,-40.2693")
(setq currobj (ssadd (entlast) currobj))
(command "_layer" "set" "nitride" "")
(setq coords (list 
(list 4800.2625 -40.2693) 
(list 4800.5625 -30.2693) 
(list 4800.5625 -30.2693) 
(list 4800.5625 -29.2693) 
(list 4874.585 -30.0193) 
(list 4874.585 -25.0763) 
(list 4800.5625 -25.8263) 
(list 4800.5625 -24.8263) 
(list 4800.5625 -24.8263) 
(list 4800.2625 -14.8263) 
(list 4799.7375 -14.8263) 
(list 4799.4375 -24.8263) 
(list 4799.4375 -24.8263) 
(list 4799.4375 -25.8263) 
(list 4725.415 -25.0763) 
(list 4725.415 -30.0193) 
(list 4799.4375 -29.2693) 
(list 4799.4375 -30.2693) 
(list 4799.4375 -30.2693) 
(list 4799.7375 -40.2693)))
(apply 'command (append '("pline") coords '("c")))
(setq currobj (ssadd (entlast) currobj))
(command "_layer" "set" "prebias" "")
(setq coords (list 
(list 4799.4375 -40.2693) 
(list 4799.4375 -29.2693) 
(list 4725.415 -30.0193) 
(list 4725.415 -25.0763) 
(list 4799.4375 -25.8263) 
(list 4799.4375 -14.8263) 
(list 4800.5625 -14.8263) 
(list 4800.5625 -25.8263) 
(list 4874.585 -25.0763) 
(list 4874.585 -30.0193) 
(list 4800.5625 -29.2693) 
(list 4800.5625 -40.2693)))
(apply 'command (append '("pline") coords '("c")))
(setq currobj (ssadd (entlast) currobj))
(command "_layer" "set" "nitride" "")
(command "_layer" "set" "fda1" "")
(setq coords (list 
(list 4800.5625 -29.1263) 
(list 4874.585 -29.8763) 
(list 4874.585 -29.6993) 
(list 4800.5625 -29.0493)))
(apply 'command (append '("pline") coords '("c")))
(setq currobj (ssadd (entlast) currobj))
(setq coords (list 
(list 4800.5625 -28.9063) 
(list 4874.585 -29.5563) 
(list 4874.585 -29.3793) 
(list 4800.5625 -28.8293)))
(apply 'command (append '("pline") coords '("c")))
(setq currobj (ssadd (entlast) currobj))
(setq coords (list 
(list 4800.5625 -28.6863) 
(list 4874.585 -29.2363) 
(list 4874.585 -29.0593) 
(list 4800.5625 -28.6093)))
(apply 'command (append '("pline") coords '("c")))
(setq currobj (ssadd (entlast) currobj))
(setq coords (list 
(list 4800.5625 -28.4663) 
(list 4874.585 -28.9163) 
(list 4874.585 -28.7393) 
(list 4800.5625 -28.3893)))
(apply 'command (append '("pline") coords '("c")))
(setq currobj (ssadd (entlast) currobj))
(setq coords (list 
(list 4800.5625 -28.2463) 
(list 4874.585 -28.5963) 
(list 4874.585 -28.4193) 
(list 4800.5625 -28.1693)))
(apply 'command (append '("pline") coords '("c")))
(setq currobj (ssadd (entlast) currobj))
(setq coords (list 
(list 4800.5625 -28.0263) 
(list 4874.585 -28.2763) 
(list 4874.585 -28.0993) 
(list 4800.5625 -27.9493)))
(apply 'command (append '("pline") coords '("c")))
(setq currobj (ssadd (entlast) currobj))
(setq coords (list 
(list 4800.5625 -27.8063) 
(list 4874.585 -27.9563) 
(list 4874.585 -27.7793) 
(list 4800.5625 -27.7293)))
(apply 'command (append '("pline") coords '("c")))
(setq currobj (ssadd (entlast) currobj))
(setq coords (list 
(list 4800.5625 -27.5863) 
(list 4874.585 -27.6363) 
(list 4874.585 -27.4593) 
(list 4800.5625 -27.5093)))
(apply 'command (append '("pline") coords '("c")))
(setq currobj (ssadd (entlast) currobj))
(setq coords (list 
(list 4800.5625 -27.3663) 
(list 4874.585 -27.3163) 
(list 4874.585 -27.1393) 
(list 4800.5625 -27.2893)))
(apply 'command (append '("pline") coords '("c")))
(setq currobj (ssadd (entlast) currobj))
(setq coords (list 
(list 4800.5625 -27.1463) 
(list 4874.585 -26.9963) 
(list 4874.585 -26.8193) 
(list 4800.5625 -27.0693)))
(apply 'command (append '("pline") coords '("c")))
(setq currobj (ssadd (entlast) currobj))
(setq coords (list 
(list 4800.5625 -26.9263) 
(list 4874.585 -26.6763) 
(list 4874.585 -26.4993) 
(list 4800.5625 -26.8493)))
(apply 'command (append '("pline") coords '("c")))
(setq currobj (ssadd (entlast) currobj))
(setq coords (list 
(list 4800.5625 -26.7063) 
(list 4874.585 -26.3563) 
(list 4874.585 -26.1793) 
(list 4800.5625 -26.6293)))
(apply 'command (append '("pline") coords '("c")))
(setq currobj (ssadd (entlast) currobj))
(setq coords (list 
(list 4800.5625 -26.4863) 
(list 4874.585 -26.0363) 
(list 4874.585 -25.8593) 
(list 4800.5625 -26.4093)))
(apply 'command (append '("pline") coords '("c")))
(setq currobj (ssadd (entlast) currobj))
(setq coords (list 
(list 4800.5625 -26.2663) 
(list 4874.585 -25.7163) 
(list 4874.585 -25.5393) 
(list 4800.5625 -26.1893)))
(apply 'command (append '("pline") coords '("c")))
(setq currobj (ssadd (entlast) currobj))
(setq coords (list 
(list 4800.5625 -26.0463) 
(list 4874.585 -25.3963) 
(list 4874.585 -25.2193) 
(list 4800.5625 -25.9693)))
(apply 'command (append '("pline") coords '("c")))
(setq currobj (ssadd (entlast) currobj))
(setq coords (list 
(list 4799.4375 -25.9693) 
(list 4725.415 -25.2193) 
(list 4725.415 -25.3963) 
(list 4799.4375 -26.0463)))
(apply 'command (append '("pline") coords '("c")))
(setq currobj (ssadd (entlast) currobj))
(setq coords (list 
(list 4799.4375 -26.1893) 
(list 4725.415 -25.5393) 
(list 4725.415 -25.7163) 
(list 4799.4375 -26.2663)))
(apply 'command (append '("pline") coords '("c")))
(setq currobj (ssadd (entlast) currobj))
(setq coords (list 
(list 4799.4375 -26.4093) 
(list 4725.415 -25.8593) 
(list 4725.415 -26.0363) 
(list 4799.4375 -26.4863)))
(apply 'command (append '("pline") coords '("c")))
(setq currobj (ssadd (entlast) currobj))
(setq coords (list 
(list 4799.4375 -26.6293) 
(list 4725.415 -26.1793) 
(list 4725.415 -26.3563) 
(list 4799.4375 -26.7063)))
(apply 'command (append '("pline") coords '("c")))
(setq currobj (ssadd (entlast) currobj))
(setq coords (list 
(list 4799.4375 -26.8493) 
(list 4725.415 -26.4993) 
(list 4725.415 -26.6763) 
(list 4799.4375 -26.9263)))
(apply 'command (append '("pline") coords '("c")))
(setq currobj (ssadd (entlast) currobj))
(setq coords (list 
(list 4799.4375 -27.0693) 
(list 4725.415 -26.8193) 
(list 4725.415 -26.9963) 
(list 4799.4375 -27.1463)))
(apply 'command (append '("pline") coords '("c")))
(setq currobj (ssadd (entlast) currobj))
(setq coords (list 
(list 4799.4375 -27.2893) 
(list 4725.415 -27.1393) 
(list 4725.415 -27.3163) 
(list 4799.4375 -27.3663)))
(apply 'command (append '("pline") coords '("c")))
(setq currobj (ssadd (entlast) currobj))
(setq coords (list 
(list 4799.4375 -27.5093) 
(list 4725.415 -27.4593) 
(list 4725.415 -27.6363) 
(list 4799.4375 -27.5863)))
(apply 'command (append '("pline") coords '("c")))
(setq currobj (ssadd (entlast) currobj))
(setq coords (list 
(list 4799.4375 -27.7293) 
(list 4725.415 -27.7793) 
(list 4725.415 -27.9563) 
(list 4799.4375 -27.8063)))
(apply 'command (append '("pline") coords '("c")))
(setq currobj (ssadd (entlast) currobj))
(setq coords (list 
(list 4799.4375 -27.9493) 
(list 4725.415 -28.0993) 
(list 4725.415 -28.2763) 
(list 4799.4375 -28.0263)))
(apply 'command (append '("pline") coords '("c")))
(setq currobj (ssadd (entlast) currobj))
(setq coords (list 
(list 4799.4375 -28.1693) 
(list 4725.415 -28.4193) 
(list 4725.415 -28.5963) 
(list 4799.4375 -28.2463)))
(apply 'command (append '("pline") coords '("c")))
(setq currobj (ssadd (entlast) currobj))
(setq coords (list 
(list 4799.4375 -28.3893) 
(list 4725.415 -28.7393) 
(list 4725.415 -28.9163) 
(list 4799.4375 -28.4663)))
(apply 'command (append '("pline") coords '("c")))
(setq currobj (ssadd (entlast) currobj))
(setq coords (list 
(list 4799.4375 -28.6093) 
(list 4725.415 -29.0593) 
(list 4725.415 -29.2363) 
(list 4799.4375 -28.6863)))
(apply 'command (append '("pline") coords '("c")))
(setq currobj (ssadd (entlast) currobj))
(setq coords (list 
(list 4799.4375 -28.8293) 
(list 4725.415 -29.3793) 
(list 4725.415 -29.5563) 
(list 4799.4375 -28.9063)))
(apply 'command (append '("pline") coords '("c")))
(setq currobj (ssadd (entlast) currobj))
(setq coords (list 
(list 4799.4375 -29.0493) 
(list 4725.415 -29.6993) 
(list 4725.415 -29.8763) 
(list 4799.4375 -29.1263)))
(apply 'command (append '("pline") coords '("c")))
(setq currobj (ssadd (entlast) currobj))
(command "_layer" "set" "nitride" "")
(command "_layer" "set" "text" "")
(command "_circle" "4799.0625,-40.2693" "0.075")
(command "_circle" "4799.0625,-39.9693" "0.075")
(command "_circle" "4799.0625,-39.6693" "0.075")
(command "_circle" "4799.0625,-39.3693" "0.075")
(command "_circle" "4799.0625,-39.0693" "0.075")
(command "_circle" "4798.7625,-40.2693" "0.075")
(command "_circle" "4798.7625,-39.9693" "0.075")
(command "_circle" "4798.7625,-39.6693" "0.075")
(command "_circle" "4798.7625,-39.3693" "0.075")
(command "_circle" "4798.7625,-39.0693" "0.075")
(command "_circle" "4798.4625,-40.2693" "0.075")
(command "_circle" "4798.4625,-39.9693" "0.075")
(command "_circle" "4798.4625,-39.6693" "0.075")
(command "_circle" "4798.4625,-39.3693" "0.075")
(command "_circle" "4798.4625,-39.0693" "0.075")
(command "_circle" "4798.1625,-40.2693" "0.075")
(command "_circle" "4798.1625,-39.9693" "0.075")
(command "_circle" "4798.1625,-39.6693" "0.075")
(command "_circle" "4798.1625,-39.3693" "0.075")
(command "_circle" "4798.1625,-39.0693" "0.075")
(command "_circle" "4797.8625,-40.2693" "0.075")
(command "_circle" "4797.8625,-39.9693" "0.075")
(command "_circle" "4797.8625,-39.6693" "0.075")
(command "_circle" "4797.8625,-39.3693" "0.075")
(command "_circle" "4797.8625,-39.0693" "0.075")
(command "_layer" "set" "nitride" "")
(setq coords (list 
(list 4800.2625 -14.8263) 
(list 4800.2625 100.8184) 
(list 4799.7375 100.8184) 
(list 4799.7375 -14.8263)))
(apply 'command (append '("pline") coords '("c")))
(setq currobj (ssadd (entlast) currobj))
(command "_layer" "set" "prebias" "")
(command "_rectangle" "4799.7375,-14.8263" "4800.2625,100.8184")
(setq currobj (ssadd (entlast) currobj))
(command "_layer" "set" "nitride" "")
(setq coords (list 
(list 4800.2625 100.8184) 
(list 4800.5625 110.8184) 
(list 4800.5625 110.8184) 
(list 4800.5625 111.8184) 
(list 4874.585 111.0684) 
(list 4874.585 116.0114) 
(list 4800.5625 115.2614) 
(list 4800.5625 116.2614) 
(list 4800.5625 116.2614) 
(list 4800.2625 126.2614) 
(list 4799.7375 126.2614) 
(list 4799.4375 116.2614) 
(list 4799.4375 116.2614) 
(list 4799.4375 115.2614) 
(list 4725.415 116.0114) 
(list 4725.415 111.0684) 
(list 4799.4375 111.8184) 
(list 4799.4375 110.8184) 
(list 4799.4375 110.8184) 
(list 4799.7375 100.8184)))
(apply 'command (append '("pline") coords '("c")))
(setq currobj (ssadd (entlast) currobj))
(command "_layer" "set" "prebias" "")
(setq coords (list 
(list 4799.4375 100.8184) 
(list 4799.4375 111.8184) 
(list 4725.415 111.0684) 
(list 4725.415 116.0114) 
(list 4799.4375 115.2614) 
(list 4799.4375 126.2614) 
(list 4800.5625 126.2614) 
(list 4800.5625 115.2614) 
(list 4874.585 116.0114) 
(list 4874.585 111.0684) 
(list 4800.5625 111.8184) 
(list 4800.5625 100.8184)))
(apply 'command (append '("pline") coords '("c")))
(setq currobj (ssadd (entlast) currobj))
(command "_layer" "set" "nitride" "")
(command "_layer" "set" "fda1" "")
(setq coords (list 
(list 4800.5625 111.9614) 
(list 4874.585 111.2114) 
(list 4874.585 111.3884) 
(list 4800.5625 112.0384)))
(apply 'command (append '("pline") coords '("c")))
(setq currobj (ssadd (entlast) currobj))
(setq coords (list 
(list 4800.5625 112.1814) 
(list 4874.585 111.5314) 
(list 4874.585 111.7084) 
(list 4800.5625 112.2584)))
(apply 'command (append '("pline") coords '("c")))
(setq currobj (ssadd (entlast) currobj))
(setq coords (list 
(list 4800.5625 112.4014) 
(list 4874.585 111.8514) 
(list 4874.585 112.0284) 
(list 4800.5625 112.4784)))
(apply 'command (append '("pline") coords '("c")))
(setq currobj (ssadd (entlast) currobj))
(setq coords (list 
(list 4800.5625 112.6214) 
(list 4874.585 112.1714) 
(list 4874.585 112.3484) 
(list 4800.5625 112.6984)))
(apply 'command (append '("pline") coords '("c")))
(setq currobj (ssadd (entlast) currobj))
(setq coords (list 
(list 4800.5625 112.8414) 
(list 4874.585 112.4914) 
(list 4874.585 112.6684) 
(list 4800.5625 112.9184)))
(apply 'command (append '("pline") coords '("c")))
(setq currobj (ssadd (entlast) currobj))
(setq coords (list 
(list 4800.5625 113.0614) 
(list 4874.585 112.8114) 
(list 4874.585 112.9884) 
(list 4800.5625 113.1384)))
(apply 'command (append '("pline") coords '("c")))
(setq currobj (ssadd (entlast) currobj))
(setq coords (list 
(list 4800.5625 113.2814) 
(list 4874.585 113.1314) 
(list 4874.585 113.3084) 
(list 4800.5625 113.3584)))
(apply 'command (append '("pline") coords '("c")))
(setq currobj (ssadd (entlast) currobj))
(setq coords (list 
(list 4800.5625 113.5014) 
(list 4874.585 113.4514) 
(list 4874.585 113.6284) 
(list 4800.5625 113.5784)))
(apply 'command (append '("pline") coords '("c")))
(setq currobj (ssadd (entlast) currobj))
(setq coords (list 
(list 4800.5625 113.7214) 
(list 4874.585 113.7714) 
(list 4874.585 113.9484) 
(list 4800.5625 113.7984)))
(apply 'command (append '("pline") coords '("c")))
(setq currobj (ssadd (entlast) currobj))
(setq coords (list 
(list 4800.5625 113.9414) 
(list 4874.585 114.0914) 
(list 4874.585 114.2684) 
(list 4800.5625 114.0184)))
(apply 'command (append '("pline") coords '("c")))
(setq currobj (ssadd (entlast) currobj))
(setq coords (list 
(list 4800.5625 114.1614) 
(list 4874.585 114.4114) 
(list 4874.585 114.5884) 
(list 4800.5625 114.2384)))
(apply 'command (append '("pline") coords '("c")))
(setq currobj (ssadd (entlast) currobj))
(setq coords (list 
(list 4800.5625 114.3814) 
(list 4874.585 114.7314) 
(list 4874.585 114.9084) 
(list 4800.5625 114.4584)))
(apply 'command (append '("pline") coords '("c")))
(setq currobj (ssadd (entlast) currobj))
(setq coords (list 
(list 4800.5625 114.6014) 
(list 4874.585 115.0514) 
(list 4874.585 115.2284) 
(list 4800.5625 114.6784)))
(apply 'command (append '("pline") coords '("c")))
(setq currobj (ssadd (entlast) currobj))
(setq coords (list 
(list 4800.5625 114.8214) 
(list 4874.585 115.3714) 
(list 4874.585 115.5484) 
(list 4800.5625 114.8984)))
(apply 'command (append '("pline") coords '("c")))
(setq currobj (ssadd (entlast) currobj))
(setq coords (list 
(list 4800.5625 115.0414) 
(list 4874.585 115.6914) 
(list 4874.585 115.8684) 
(list 4800.5625 115.1184)))
(apply 'command (append '("pline") coords '("c")))
(setq currobj (ssadd (entlast) currobj))
(setq coords (list 
(list 4799.4375 115.1184) 
(list 4725.415 115.8684) 
(list 4725.415 115.6914) 
(list 4799.4375 115.0414)))
(apply 'command (append '("pline") coords '("c")))
(setq currobj (ssadd (entlast) currobj))
(setq coords (list 
(list 4799.4375 114.8984) 
(list 4725.415 115.5484) 
(list 4725.415 115.3714) 
(list 4799.4375 114.8214)))
(apply 'command (append '("pline") coords '("c")))
(setq currobj (ssadd (entlast) currobj))
(setq coords (list 
(list 4799.4375 114.6784) 
(list 4725.415 115.2284) 
(list 4725.415 115.0514) 
(list 4799.4375 114.6014)))
(apply 'command (append '("pline") coords '("c")))
(setq currobj (ssadd (entlast) currobj))
(setq coords (list 
(list 4799.4375 114.4584) 
(list 4725.415 114.9084) 
(list 4725.415 114.7314) 
(list 4799.4375 114.3814)))
(apply 'command (append '("pline") coords '("c")))
(setq currobj (ssadd (entlast) currobj))
(setq coords (list 
(list 4799.4375 114.2384) 
(list 4725.415 114.5884) 
(list 4725.415 114.4114) 
(list 4799.4375 114.1614)))
(apply 'command (append '("pline") coords '("c")))
(setq currobj (ssadd (entlast) currobj))
(setq coords (list 
(list 4799.4375 114.0184) 
(list 4725.415 114.2684) 
(list 4725.415 114.0914) 
(list 4799.4375 113.9414)))
(apply 'command (append '("pline") coords '("c")))
(setq currobj (ssadd (entlast) currobj))
(setq coords (list 
(list 4799.4375 113.7984) 
(list 4725.415 113.9484) 
(list 4725.415 113.7714) 
(list 4799.4375 113.7214)))
(apply 'command (append '("pline") coords '("c")))
(setq currobj (ssadd (entlast) currobj))
(setq coords (list 
(list 4799.4375 113.5784) 
(list 4725.415 113.6284) 
(list 4725.415 113.4514) 
(list 4799.4375 113.5014)))
(apply 'command (append '("pline") coords '("c")))
(setq currobj (ssadd (entlast) currobj))
(setq coords (list 
(list 4799.4375 113.3584) 
(list 4725.415 113.3084) 
(list 4725.415 113.1314) 
(list 4799.4375 113.2814)))
(apply 'command (append '("pline") coords '("c")))
(setq currobj (ssadd (entlast) currobj))
(setq coords (list 
(list 4799.4375 113.1384) 
(list 4725.415 112.9884) 
(list 4725.415 112.8114) 
(list 4799.4375 113.0614)))
(apply 'command (append '("pline") coords '("c")))
(setq currobj (ssadd (entlast) currobj))
(setq coords (list 
(list 4799.4375 112.9184) 
(list 4725.415 112.6684) 
(list 4725.415 112.4914) 
(list 4799.4375 112.8414)))
(apply 'command (append '("pline") coords '("c")))
(setq currobj (ssadd (entlast) currobj))
(setq coords (list 
(list 4799.4375 112.6984) 
(list 4725.415 112.3484) 
(list 4725.415 112.1714) 
(list 4799.4375 112.6214)))
(apply 'command (append '("pline") coords '("c")))
(setq currobj (ssadd (entlast) currobj))
(setq coords (list 
(list 4799.4375 112.4784) 
(list 4725.415 112.0284) 
(list 4725.415 111.8514) 
(list 4799.4375 112.4014)))
(apply 'command (append '("pline") coords '("c")))
(setq currobj (ssadd (entlast) currobj))
(setq coords (list 
(list 4799.4375 112.2584) 
(list 4725.415 111.7084) 
(list 4725.415 111.5314) 
(list 4799.4375 112.1814)))
(apply 'command (append '("pline") coords '("c")))
(setq currobj (ssadd (entlast) currobj))
(setq coords (list 
(list 4799.4375 112.0384) 
(list 4725.415 111.3884) 
(list 4725.415 111.2114) 
(list 4799.4375 111.9614)))
(apply 'command (append '("pline") coords '("c")))
(setq currobj (ssadd (entlast) currobj))
(command "_layer" "set" "nitride" "")
(command "_layer" "set" "text" "")
(command "_circle" "4799.0625,100.8184" "0.075")
(command "_circle" "4799.0625,101.1184" "0.075")
(command "_circle" "4799.0625,101.4184" "0.075")
(command "_circle" "4799.0625,101.7184" "0.075")
(command "_circle" "4799.0625,102.0184" "0.075")
(command "_circle" "4798.7625,100.8184" "0.075")
(command "_circle" "4798.7625,101.1184" "0.075")
(command "_circle" "4798.7625,101.4184" "0.075")
(command "_circle" "4798.7625,101.7184" "0.075")
(command "_circle" "4798.7625,102.0184" "0.075")
(command "_circle" "4798.4625,100.8184" "0.075")
(command "_circle" "4798.4625,101.1184" "0.075")
(command "_circle" "4798.4625,101.4184" "0.075")
(command "_circle" "4798.4625,101.7184" "0.075")
(command "_circle" "4798.4625,102.0184" "0.075")
(command "_circle" "4798.1625,100.8184" "0.075")
(command "_circle" "4798.1625,101.1184" "0.075")
(command "_circle" "4798.1625,101.4184" "0.075")
(command "_circle" "4798.1625,101.7184" "0.075")
(command "_circle" "4798.1625,102.0184" "0.075")
(command "_circle" "4797.8625,100.8184" "0.075")
(command "_circle" "4797.8625,101.1184" "0.075")
(command "_circle" "4797.8625,101.4184" "0.075")
(command "_circle" "4797.8625,101.7184" "0.075")
(command "_circle" "4797.8625,102.0184" "0.075")
(command "_layer" "set" "nitride" "")
(setq coords (list 
(list 4800.2625 126.2614) 
(list 4800.2625 241.9061) 
(list 4799.7375 241.9061) 
(list 4799.7375 126.2614)))
(apply 'command (append '("pline") coords '("c")))
(setq currobj (ssadd (entlast) currobj))
(command "_layer" "set" "prebias" "")
(command "_rectangle" "4799.7375,126.2614" "4800.2625,241.9061")
(setq currobj (ssadd (entlast) currobj))
(command "_layer" "set" "nitride" "")
(setq coords (list 
(list 4800.2625 241.9061) 
(list 4800.5625 251.9061) 
(list 4800.5625 251.9061) 
(list 4800.5625 252.9061) 
(list 4874.585 252.1561) 
(list 4874.585 257.0991) 
(list 4800.5625 256.3491) 
(list 4800.5625 257.3491) 
(list 4800.5625 257.3491) 
(list 4800.2625 267.3491) 
(list 4799.7375 267.3491) 
(list 4799.4375 257.3491) 
(list 4799.4375 257.3491) 
(list 4799.4375 256.3491) 
(list 4725.415 257.0991) 
(list 4725.415 252.1561) 
(list 4799.4375 252.9061) 
(list 4799.4375 251.9061) 
(list 4799.4375 251.9061) 
(list 4799.7375 241.9061)))
(apply 'command (append '("pline") coords '("c")))
(setq currobj (ssadd (entlast) currobj))
(command "_layer" "set" "prebias" "")
(setq coords (list 
(list 4799.4375 241.9061) 
(list 4799.4375 252.9061) 
(list 4725.415 252.1561) 
(list 4725.415 257.0991) 
(list 4799.4375 256.3491) 
(list 4799.4375 267.3491) 
(list 4800.5625 267.3491) 
(list 4800.5625 256.3491) 
(list 4874.585 257.0991) 
(list 4874.585 252.1561) 
(list 4800.5625 252.9061) 
(list 4800.5625 241.9061)))
(apply 'command (append '("pline") coords '("c")))
(setq currobj (ssadd (entlast) currobj))
(command "_layer" "set" "nitride" "")
(command "_layer" "set" "fda1" "")
(setq coords (list 
(list 4800.5625 253.0491) 
(list 4874.585 252.2991) 
(list 4874.585 252.4761) 
(list 4800.5625 253.1261)))
(apply 'command (append '("pline") coords '("c")))
(setq currobj (ssadd (entlast) currobj))
(setq coords (list 
(list 4800.5625 253.2691) 
(list 4874.585 252.6191) 
(list 4874.585 252.7961) 
(list 4800.5625 253.3461)))
(apply 'command (append '("pline") coords '("c")))
(setq currobj (ssadd (entlast) currobj))
(setq coords (list 
(list 4800.5625 253.4891) 
(list 4874.585 252.9391) 
(list 4874.585 253.1161) 
(list 4800.5625 253.5661)))
(apply 'command (append '("pline") coords '("c")))
(setq currobj (ssadd (entlast) currobj))
(setq coords (list 
(list 4800.5625 253.7091) 
(list 4874.585 253.2591) 
(list 4874.585 253.4361) 
(list 4800.5625 253.7861)))
(apply 'command (append '("pline") coords '("c")))
(setq currobj (ssadd (entlast) currobj))
(setq coords (list 
(list 4800.5625 253.9291) 
(list 4874.585 253.5791) 
(list 4874.585 253.7561) 
(list 4800.5625 254.0061)))
(apply 'command (append '("pline") coords '("c")))
(setq currobj (ssadd (entlast) currobj))
(setq coords (list 
(list 4800.5625 254.1491) 
(list 4874.585 253.8991) 
(list 4874.585 254.0761) 
(list 4800.5625 254.2261)))
(apply 'command (append '("pline") coords '("c")))
(setq currobj (ssadd (entlast) currobj))
(setq coords (list 
(list 4800.5625 254.3691) 
(list 4874.585 254.2191) 
(list 4874.585 254.3961) 
(list 4800.5625 254.4461)))
(apply 'command (append '("pline") coords '("c")))
(setq currobj (ssadd (entlast) currobj))
(setq coords (list 
(list 4800.5625 254.5891) 
(list 4874.585 254.5391) 
(list 4874.585 254.7161) 
(list 4800.5625 254.6661)))
(apply 'command (append '("pline") coords '("c")))
(setq currobj (ssadd (entlast) currobj))
(setq coords (list 
(list 4800.5625 254.8091) 
(list 4874.585 254.8591) 
(list 4874.585 255.0361) 
(list 4800.5625 254.8861)))
(apply 'command (append '("pline") coords '("c")))
(setq currobj (ssadd (entlast) currobj))
(setq coords (list 
(list 4800.5625 255.0291) 
(list 4874.585 255.1791) 
(list 4874.585 255.3561) 
(list 4800.5625 255.1061)))
(apply 'command (append '("pline") coords '("c")))
(setq currobj (ssadd (entlast) currobj))
(setq coords (list 
(list 4800.5625 255.2491) 
(list 4874.585 255.4991) 
(list 4874.585 255.6761) 
(list 4800.5625 255.3261)))
(apply 'command (append '("pline") coords '("c")))
(setq currobj (ssadd (entlast) currobj))
(setq coords (list 
(list 4800.5625 255.4691) 
(list 4874.585 255.8191) 
(list 4874.585 255.9961) 
(list 4800.5625 255.5461)))
(apply 'command (append '("pline") coords '("c")))
(setq currobj (ssadd (entlast) currobj))
(setq coords (list 
(list 4800.5625 255.6891) 
(list 4874.585 256.1391) 
(list 4874.585 256.3161) 
(list 4800.5625 255.7661)))
(apply 'command (append '("pline") coords '("c")))
(setq currobj (ssadd (entlast) currobj))
(setq coords (list 
(list 4800.5625 255.9091) 
(list 4874.585 256.4591) 
(list 4874.585 256.6361) 
(list 4800.5625 255.9861)))
(apply 'command (append '("pline") coords '("c")))
(setq currobj (ssadd (entlast) currobj))
(setq coords (list 
(list 4800.5625 256.1291) 
(list 4874.585 256.7791) 
(list 4874.585 256.9561) 
(list 4800.5625 256.2061)))
(apply 'command (append '("pline") coords '("c")))
(setq currobj (ssadd (entlast) currobj))
(setq coords (list 
(list 4799.4375 256.2061) 
(list 4725.415 256.9561) 
(list 4725.415 256.7791) 
(list 4799.4375 256.1291)))
(apply 'command (append '("pline") coords '("c")))
(setq currobj (ssadd (entlast) currobj))
(setq coords (list 
(list 4799.4375 255.9861) 
(list 4725.415 256.6361) 
(list 4725.415 256.4591) 
(list 4799.4375 255.9091)))
(apply 'command (append '("pline") coords '("c")))
(setq currobj (ssadd (entlast) currobj))
(setq coords (list 
(list 4799.4375 255.7661) 
(list 4725.415 256.3161) 
(list 4725.415 256.1391) 
(list 4799.4375 255.6891)))
(apply 'command (append '("pline") coords '("c")))
(setq currobj (ssadd (entlast) currobj))
(setq coords (list 
(list 4799.4375 255.5461) 
(list 4725.415 255.9961) 
(list 4725.415 255.8191) 
(list 4799.4375 255.4691)))
(apply 'command (append '("pline") coords '("c")))
(setq currobj (ssadd (entlast) currobj))
(setq coords (list 
(list 4799.4375 255.3261) 
(list 4725.415 255.6761) 
(list 4725.415 255.4991) 
(list 4799.4375 255.2491)))
(apply 'command (append '("pline") coords '("c")))
(setq currobj (ssadd (entlast) currobj))
(setq coords (list 
(list 4799.4375 255.1061) 
(list 4725.415 255.3561) 
(list 4725.415 255.1791) 
(list 4799.4375 255.0291)))
(apply 'command (append '("pline") coords '("c")))
(setq currobj (ssadd (entlast) currobj))
(setq coords (list 
(list 4799.4375 254.8861) 
(list 4725.415 255.0361) 
(list 4725.415 254.8591) 
(list 4799.4375 254.8091)))
(apply 'command (append '("pline") coords '("c")))
(setq currobj (ssadd (entlast) currobj))
(setq coords (list 
(list 4799.4375 254.6661) 
(list 4725.415 254.7161) 
(list 4725.415 254.5391) 
(list 4799.4375 254.5891)))
(apply 'command (append '("pline") coords '("c")))
(setq currobj (ssadd (entlast) currobj))
(setq coords (list 
(list 4799.4375 254.4461) 
(list 4725.415 254.3961) 
(list 4725.415 254.2191) 
(list 4799.4375 254.3691)))
(apply 'command (append '("pline") coords '("c")))
(setq currobj (ssadd (entlast) currobj))
(setq coords (list 
(list 4799.4375 254.2261) 
(list 4725.415 254.0761) 
(list 4725.415 253.8991) 
(list 4799.4375 254.1491)))
(apply 'command (append '("pline") coords '("c")))
(setq currobj (ssadd (entlast) currobj))
(setq coords (list 
(list 4799.4375 254.0061) 
(list 4725.415 253.7561) 
(list 4725.415 253.5791) 
(list 4799.4375 253.9291)))
(apply 'command (append '("pline") coords '("c")))
(setq currobj (ssadd (entlast) currobj))
(setq coords (list 
(list 4799.4375 253.7861) 
(list 4725.415 253.4361) 
(list 4725.415 253.2591) 
(list 4799.4375 253.7091)))
(apply 'command (append '("pline") coords '("c")))
(setq currobj (ssadd (entlast) currobj))
(setq coords (list 
(list 4799.4375 253.5661) 
(list 4725.415 253.1161) 
(list 4725.415 252.9391) 
(list 4799.4375 253.4891)))
(apply 'command (append '("pline") coords '("c")))
(setq currobj (ssadd (entlast) currobj))
(setq coords (list 
(list 4799.4375 253.3461) 
(list 4725.415 252.7961) 
(list 4725.415 252.6191) 
(list 4799.4375 253.2691)))
(apply 'command (append '("pline") coords '("c")))
(setq currobj (ssadd (entlast) currobj))
(setq coords (list 
(list 4799.4375 253.1261) 
(list 4725.415 252.4761) 
(list 4725.415 252.2991) 
(list 4799.4375 253.0491)))
(apply 'command (append '("pline") coords '("c")))
(setq currobj (ssadd (entlast) currobj))
(command "_layer" "set" "nitride" "")
(command "_layer" "set" "text" "")
(command "_circle" "4799.0625,241.9061" "0.075")
(command "_circle" "4799.0625,242.2061" "0.075")
(command "_circle" "4799.0625,242.5061" "0.075")
(command "_circle" "4799.0625,242.8061" "0.075")
(command "_circle" "4799.0625,243.1061" "0.075")
(command "_circle" "4798.7625,241.9061" "0.075")
(command "_circle" "4798.7625,242.2061" "0.075")
(command "_circle" "4798.7625,242.5061" "0.075")
(command "_circle" "4798.7625,242.8061" "0.075")
(command "_circle" "4798.7625,243.1061" "0.075")
(command "_circle" "4798.4625,241.9061" "0.075")
(command "_circle" "4798.4625,242.2061" "0.075")
(command "_circle" "4798.4625,242.5061" "0.075")
(command "_circle" "4798.4625,242.8061" "0.075")
(command "_circle" "4798.4625,243.1061" "0.075")
(command "_circle" "4798.1625,241.9061" "0.075")
(command "_circle" "4798.1625,242.2061" "0.075")
(command "_circle" "4798.1625,242.5061" "0.075")
(command "_circle" "4798.1625,242.8061" "0.075")
(command "_circle" "4798.1625,243.1061" "0.075")
(command "_circle" "4797.8625,241.9061" "0.075")
(command "_circle" "4797.8625,242.2061" "0.075")
(command "_circle" "4797.8625,242.5061" "0.075")
(command "_circle" "4797.8625,242.8061" "0.075")
(command "_circle" "4797.8625,243.1061" "0.075")
(command "_layer" "set" "nitride" "")
(setq coords (list 
(list 4800.2625 267.3491) 
(list 4800.2625 382.9939) 
(list 4799.7375 382.9939) 
(list 4799.7375 267.3491)))
(apply 'command (append '("pline") coords '("c")))
(setq currobj (ssadd (entlast) currobj))
(command "_layer" "set" "prebias" "")
(command "_rectangle" "4799.7375,267.3491" "4800.2625,382.9939")
(setq currobj (ssadd (entlast) currobj))
(command "_layer" "set" "nitride" "")
(setq coords (list 
(list 4800.2625 382.9939) 
(list 4800.5625 392.9939) 
(list 4800.5625 392.9939) 
(list 4800.5625 393.9939) 
(list 4874.585 393.2439) 
(list 4874.585 398.1869) 
(list 4800.5625 397.4369) 
(list 4800.5625 398.4369) 
(list 4800.5625 398.4369) 
(list 4800.2625 408.4369) 
(list 4799.7375 408.4369) 
(list 4799.4375 398.4369) 
(list 4799.4375 398.4369) 
(list 4799.4375 397.4369) 
(list 4725.415 398.1869) 
(list 4725.415 393.2439) 
(list 4799.4375 393.9939) 
(list 4799.4375 392.9939) 
(list 4799.4375 392.9939) 
(list 4799.7375 382.9939)))
(apply 'command (append '("pline") coords '("c")))
(setq currobj (ssadd (entlast) currobj))
(command "_layer" "set" "prebias" "")
(setq coords (list 
(list 4799.4375 382.9939) 
(list 4799.4375 393.9939) 
(list 4725.415 393.2439) 
(list 4725.415 398.1869) 
(list 4799.4375 397.4369) 
(list 4799.4375 408.4369) 
(list 4800.5625 408.4369) 
(list 4800.5625 397.4369) 
(list 4874.585 398.1869) 
(list 4874.585 393.2439) 
(list 4800.5625 393.9939) 
(list 4800.5625 382.9939)))
(apply 'command (append '("pline") coords '("c")))
(setq currobj (ssadd (entlast) currobj))
(command "_layer" "set" "nitride" "")
(command "_layer" "set" "fda1" "")
(setq coords (list 
(list 4800.5625 394.1369) 
(list 4874.585 393.3869) 
(list 4874.585 393.5639) 
(list 4800.5625 394.2139)))
(apply 'command (append '("pline") coords '("c")))
(setq currobj (ssadd (entlast) currobj))
(setq coords (list 
(list 4800.5625 394.3569) 
(list 4874.585 393.7069) 
(list 4874.585 393.8839) 
(list 4800.5625 394.4339)))
(apply 'command (append '("pline") coords '("c")))
(setq currobj (ssadd (entlast) currobj))
(setq coords (list 
(list 4800.5625 394.5769) 
(list 4874.585 394.0269) 
(list 4874.585 394.2039) 
(list 4800.5625 394.6539)))
(apply 'command (append '("pline") coords '("c")))
(setq currobj (ssadd (entlast) currobj))
(setq coords (list 
(list 4800.5625 394.7969) 
(list 4874.585 394.3469) 
(list 4874.585 394.5239) 
(list 4800.5625 394.8739)))
(apply 'command (append '("pline") coords '("c")))
(setq currobj (ssadd (entlast) currobj))
(setq coords (list 
(list 4800.5625 395.0169) 
(list 4874.585 394.6669) 
(list 4874.585 394.8439) 
(list 4800.5625 395.0939)))
(apply 'command (append '("pline") coords '("c")))
(setq currobj (ssadd (entlast) currobj))
(setq coords (list 
(list 4800.5625 395.2369) 
(list 4874.585 394.9869) 
(list 4874.585 395.1639) 
(list 4800.5625 395.3139)))
(apply 'command (append '("pline") coords '("c")))
(setq currobj (ssadd (entlast) currobj))
(setq coords (list 
(list 4800.5625 395.4569) 
(list 4874.585 395.3069) 
(list 4874.585 395.4839) 
(list 4800.5625 395.5339)))
(apply 'command (append '("pline") coords '("c")))
(setq currobj (ssadd (entlast) currobj))
(setq coords (list 
(list 4800.5625 395.6769) 
(list 4874.585 395.6269) 
(list 4874.585 395.8039) 
(list 4800.5625 395.7539)))
(apply 'command (append '("pline") coords '("c")))
(setq currobj (ssadd (entlast) currobj))
(setq coords (list 
(list 4800.5625 395.8969) 
(list 4874.585 395.9469) 
(list 4874.585 396.1239) 
(list 4800.5625 395.9739)))
(apply 'command (append '("pline") coords '("c")))
(setq currobj (ssadd (entlast) currobj))
(setq coords (list 
(list 4800.5625 396.1169) 
(list 4874.585 396.2669) 
(list 4874.585 396.4439) 
(list 4800.5625 396.1939)))
(apply 'command (append '("pline") coords '("c")))
(setq currobj (ssadd (entlast) currobj))
(setq coords (list 
(list 4800.5625 396.3369) 
(list 4874.585 396.5869) 
(list 4874.585 396.7639) 
(list 4800.5625 396.4139)))
(apply 'command (append '("pline") coords '("c")))
(setq currobj (ssadd (entlast) currobj))
(setq coords (list 
(list 4800.5625 396.5569) 
(list 4874.585 396.9069) 
(list 4874.585 397.0839) 
(list 4800.5625 396.6339)))
(apply 'command (append '("pline") coords '("c")))
(setq currobj (ssadd (entlast) currobj))
(setq coords (list 
(list 4800.5625 396.7769) 
(list 4874.585 397.2269) 
(list 4874.585 397.4039) 
(list 4800.5625 396.8539)))
(apply 'command (append '("pline") coords '("c")))
(setq currobj (ssadd (entlast) currobj))
(setq coords (list 
(list 4800.5625 396.9969) 
(list 4874.585 397.5469) 
(list 4874.585 397.7239) 
(list 4800.5625 397.0739)))
(apply 'command (append '("pline") coords '("c")))
(setq currobj (ssadd (entlast) currobj))
(setq coords (list 
(list 4800.5625 397.2169) 
(list 4874.585 397.8669) 
(list 4874.585 398.0439) 
(list 4800.5625 397.2939)))
(apply 'command (append '("pline") coords '("c")))
(setq currobj (ssadd (entlast) currobj))
(setq coords (list 
(list 4799.4375 397.2939) 
(list 4725.415 398.0439) 
(list 4725.415 397.8669) 
(list 4799.4375 397.2169)))
(apply 'command (append '("pline") coords '("c")))
(setq currobj (ssadd (entlast) currobj))
(setq coords (list 
(list 4799.4375 397.0739) 
(list 4725.415 397.7239) 
(list 4725.415 397.5469) 
(list 4799.4375 396.9969)))
(apply 'command (append '("pline") coords '("c")))
(setq currobj (ssadd (entlast) currobj))
(setq coords (list 
(list 4799.4375 396.8539) 
(list 4725.415 397.4039) 
(list 4725.415 397.2269) 
(list 4799.4375 396.7769)))
(apply 'command (append '("pline") coords '("c")))
(setq currobj (ssadd (entlast) currobj))
(setq coords (list 
(list 4799.4375 396.6339) 
(list 4725.415 397.0839) 
(list 4725.415 396.9069) 
(list 4799.4375 396.5569)))
(apply 'command (append '("pline") coords '("c")))
(setq currobj (ssadd (entlast) currobj))
(setq coords (list 
(list 4799.4375 396.4139) 
(list 4725.415 396.7639) 
(list 4725.415 396.5869) 
(list 4799.4375 396.3369)))
(apply 'command (append '("pline") coords '("c")))
(setq currobj (ssadd (entlast) currobj))
(setq coords (list 
(list 4799.4375 396.1939) 
(list 4725.415 396.4439) 
(list 4725.415 396.2669) 
(list 4799.4375 396.1169)))
(apply 'command (append '("pline") coords '("c")))
(setq currobj (ssadd (entlast) currobj))
(setq coords (list 
(list 4799.4375 395.9739) 
(list 4725.415 396.1239) 
(list 4725.415 395.9469) 
(list 4799.4375 395.8969)))
(apply 'command (append '("pline") coords '("c")))
(setq currobj (ssadd (entlast) currobj))
(setq coords (list 
(list 4799.4375 395.7539) 
(list 4725.415 395.8039) 
(list 4725.415 395.6269) 
(list 4799.4375 395.6769)))
(apply 'command (append '("pline") coords '("c")))
(setq currobj (ssadd (entlast) currobj))
(setq coords (list 
(list 4799.4375 395.5339) 
(list 4725.415 395.4839) 
(list 4725.415 395.3069) 
(list 4799.4375 395.4569)))
(apply 'command (append '("pline") coords '("c")))
(setq currobj (ssadd (entlast) currobj))
(setq coords (list 
(list 4799.4375 395.3139) 
(list 4725.415 395.1639) 
(list 4725.415 394.9869) 
(list 4799.4375 395.2369)))
(apply 'command (append '("pline") coords '("c")))
(setq currobj (ssadd (entlast) currobj))
(setq coords (list 
(list 4799.4375 395.0939) 
(list 4725.415 394.8439) 
(list 4725.415 394.6669) 
(list 4799.4375 395.0169)))
(apply 'command (append '("pline") coords '("c")))
(setq currobj (ssadd (entlast) currobj))
(setq coords (list 
(list 4799.4375 394.8739) 
(list 4725.415 394.5239) 
(list 4725.415 394.3469) 
(list 4799.4375 394.7969)))
(apply 'command (append '("pline") coords '("c")))
(setq currobj (ssadd (entlast) currobj))
(setq coords (list 
(list 4799.4375 394.6539) 
(list 4725.415 394.2039) 
(list 4725.415 394.0269) 
(list 4799.4375 394.5769)))
(apply 'command (append '("pline") coords '("c")))
(setq currobj (ssadd (entlast) currobj))
(setq coords (list 
(list 4799.4375 394.4339) 
(list 4725.415 393.8839) 
(list 4725.415 393.7069) 
(list 4799.4375 394.3569)))
(apply 'command (append '("pline") coords '("c")))
(setq currobj (ssadd (entlast) currobj))
(setq coords (list 
(list 4799.4375 394.2139) 
(list 4725.415 393.5639) 
(list 4725.415 393.3869) 
(list 4799.4375 394.1369)))
(apply 'command (append '("pline") coords '("c")))
(setq currobj (ssadd (entlast) currobj))
(command "_layer" "set" "nitride" "")
(command "_layer" "set" "text" "")
(command "_circle" "4799.0625,382.9939" "0.075")
(command "_circle" "4799.0625,383.2939" "0.075")
(command "_circle" "4799.0625,383.5939" "0.075")
(command "_circle" "4799.0625,383.8939" "0.075")
(command "_circle" "4799.0625,384.1939" "0.075")
(command "_circle" "4798.7625,382.9939" "0.075")
(command "_circle" "4798.7625,383.2939" "0.075")
(command "_circle" "4798.7625,383.5939" "0.075")
(command "_circle" "4798.7625,383.8939" "0.075")
(command "_circle" "4798.7625,384.1939" "0.075")
(command "_circle" "4798.4625,382.9939" "0.075")
(command "_circle" "4798.4625,383.2939" "0.075")
(command "_circle" "4798.4625,383.5939" "0.075")
(command "_circle" "4798.4625,383.8939" "0.075")
(command "_circle" "4798.4625,384.1939" "0.075")
(command "_circle" "4798.1625,382.9939" "0.075")
(command "_circle" "4798.1625,383.2939" "0.075")
(command "_circle" "4798.1625,383.5939" "0.075")
(command "_circle" "4798.1625,383.8939" "0.075")
(command "_circle" "4798.1625,384.1939" "0.075")
(command "_circle" "4797.8625,382.9939" "0.075")
(command "_circle" "4797.8625,383.2939" "0.075")
(command "_circle" "4797.8625,383.5939" "0.075")
(command "_circle" "4797.8625,383.8939" "0.075")
(command "_circle" "4797.8625,384.1939" "0.075")
(command "_layer" "set" "nitride" "")
(setq coords (list 
(list 4800.2625 408.4369) 
(list 4800.2625 524.0816) 
(list 4799.7375 524.0816) 
(list 4799.7375 408.4369)))
(apply 'command (append '("pline") coords '("c")))
(setq currobj (ssadd (entlast) currobj))
(command "_layer" "set" "prebias" "")
(command "_rectangle" "4799.7375,408.4369" "4800.2625,524.0816")
(setq currobj (ssadd (entlast) currobj))
(command "_layer" "set" "nitride" "")
(setq coords (list 
(list 4800.2625 524.0816) 
(list 4800.5625 534.0816) 
(list 4800.5625 534.0816) 
(list 4800.5625 535.0816) 
(list 4874.585 534.3316) 
(list 4874.585 539.2746) 
(list 4800.5625 538.5246) 
(list 4800.5625 539.5246) 
(list 4800.5625 539.5246) 
(list 4800.2625 549.5246) 
(list 4799.7375 549.5246) 
(list 4799.4375 539.5246) 
(list 4799.4375 539.5246) 
(list 4799.4375 538.5246) 
(list 4725.415 539.2746) 
(list 4725.415 534.3316) 
(list 4799.4375 535.0816) 
(list 4799.4375 534.0816) 
(list 4799.4375 534.0816) 
(list 4799.7375 524.0816)))
(apply 'command (append '("pline") coords '("c")))
(setq currobj (ssadd (entlast) currobj))
(command "_layer" "set" "prebias" "")
(setq coords (list 
(list 4799.4375 524.0816) 
(list 4799.4375 535.0816) 
(list 4725.415 534.3316) 
(list 4725.415 539.2746) 
(list 4799.4375 538.5246) 
(list 4799.4375 549.5246) 
(list 4800.5625 549.5246) 
(list 4800.5625 538.5246) 
(list 4874.585 539.2746) 
(list 4874.585 534.3316) 
(list 4800.5625 535.0816) 
(list 4800.5625 524.0816)))
(apply 'command (append '("pline") coords '("c")))
(setq currobj (ssadd (entlast) currobj))
(command "_layer" "set" "nitride" "")
(command "_layer" "set" "fda1" "")
(setq coords (list 
(list 4800.5625 535.2246) 
(list 4874.585 534.4746) 
(list 4874.585 534.6516) 
(list 4800.5625 535.3016)))
(apply 'command (append '("pline") coords '("c")))
(setq currobj (ssadd (entlast) currobj))
(setq coords (list 
(list 4800.5625 535.4446) 
(list 4874.585 534.7946) 
(list 4874.585 534.9716) 
(list 4800.5625 535.5216)))
(apply 'command (append '("pline") coords '("c")))
(setq currobj (ssadd (entlast) currobj))
(setq coords (list 
(list 4800.5625 535.6646) 
(list 4874.585 535.1146) 
(list 4874.585 535.2916) 
(list 4800.5625 535.7416)))
(apply 'command (append '("pline") coords '("c")))
(setq currobj (ssadd (entlast) currobj))
(setq coords (list 
(list 4800.5625 535.8846) 
(list 4874.585 535.4346) 
(list 4874.585 535.6116) 
(list 4800.5625 535.9616)))
(apply 'command (append '("pline") coords '("c")))
(setq currobj (ssadd (entlast) currobj))
(setq coords (list 
(list 4800.5625 536.1046) 
(list 4874.585 535.7546) 
(list 4874.585 535.9316) 
(list 4800.5625 536.1816)))
(apply 'command (append '("pline") coords '("c")))
(setq currobj (ssadd (entlast) currobj))
(setq coords (list 
(list 4800.5625 536.3246) 
(list 4874.585 536.0746) 
(list 4874.585 536.2516) 
(list 4800.5625 536.4016)))
(apply 'command (append '("pline") coords '("c")))
(setq currobj (ssadd (entlast) currobj))
(setq coords (list 
(list 4800.5625 536.5446) 
(list 4874.585 536.3946) 
(list 4874.585 536.5716) 
(list 4800.5625 536.6216)))
(apply 'command (append '("pline") coords '("c")))
(setq currobj (ssadd (entlast) currobj))
(setq coords (list 
(list 4800.5625 536.7646) 
(list 4874.585 536.7146) 
(list 4874.585 536.8916) 
(list 4800.5625 536.8416)))
(apply 'command (append '("pline") coords '("c")))
(setq currobj (ssadd (entlast) currobj))
(setq coords (list 
(list 4800.5625 536.9846) 
(list 4874.585 537.0346) 
(list 4874.585 537.2116) 
(list 4800.5625 537.0616)))
(apply 'command (append '("pline") coords '("c")))
(setq currobj (ssadd (entlast) currobj))
(setq coords (list 
(list 4800.5625 537.2046) 
(list 4874.585 537.3546) 
(list 4874.585 537.5316) 
(list 4800.5625 537.2816)))
(apply 'command (append '("pline") coords '("c")))
(setq currobj (ssadd (entlast) currobj))
(setq coords (list 
(list 4800.5625 537.4246) 
(list 4874.585 537.6746) 
(list 4874.585 537.8516) 
(list 4800.5625 537.5016)))
(apply 'command (append '("pline") coords '("c")))
(setq currobj (ssadd (entlast) currobj))
(setq coords (list 
(list 4800.5625 537.6446) 
(list 4874.585 537.9946) 
(list 4874.585 538.1716) 
(list 4800.5625 537.7216)))
(apply 'command (append '("pline") coords '("c")))
(setq currobj (ssadd (entlast) currobj))
(setq coords (list 
(list 4800.5625 537.8646) 
(list 4874.585 538.3146) 
(list 4874.585 538.4916) 
(list 4800.5625 537.9416)))
(apply 'command (append '("pline") coords '("c")))
(setq currobj (ssadd (entlast) currobj))
(setq coords (list 
(list 4800.5625 538.0846) 
(list 4874.585 538.6346) 
(list 4874.585 538.8116) 
(list 4800.5625 538.1616)))
(apply 'command (append '("pline") coords '("c")))
(setq currobj (ssadd (entlast) currobj))
(setq coords (list 
(list 4800.5625 538.3046) 
(list 4874.585 538.9546) 
(list 4874.585 539.1316) 
(list 4800.5625 538.3816)))
(apply 'command (append '("pline") coords '("c")))
(setq currobj (ssadd (entlast) currobj))
(setq coords (list 
(list 4799.4375 538.3816) 
(list 4725.415 539.1316) 
(list 4725.415 538.9546) 
(list 4799.4375 538.3046)))
(apply 'command (append '("pline") coords '("c")))
(setq currobj (ssadd (entlast) currobj))
(setq coords (list 
(list 4799.4375 538.1616) 
(list 4725.415 538.8116) 
(list 4725.415 538.6346) 
(list 4799.4375 538.0846)))
(apply 'command (append '("pline") coords '("c")))
(setq currobj (ssadd (entlast) currobj))
(setq coords (list 
(list 4799.4375 537.9416) 
(list 4725.415 538.4916) 
(list 4725.415 538.3146) 
(list 4799.4375 537.8646)))
(apply 'command (append '("pline") coords '("c")))
(setq currobj (ssadd (entlast) currobj))
(setq coords (list 
(list 4799.4375 537.7216) 
(list 4725.415 538.1716) 
(list 4725.415 537.9946) 
(list 4799.4375 537.6446)))
(apply 'command (append '("pline") coords '("c")))
(setq currobj (ssadd (entlast) currobj))
(setq coords (list 
(list 4799.4375 537.5016) 
(list 4725.415 537.8516) 
(list 4725.415 537.6746) 
(list 4799.4375 537.4246)))
(apply 'command (append '("pline") coords '("c")))
(setq currobj (ssadd (entlast) currobj))
(setq coords (list 
(list 4799.4375 537.2816) 
(list 4725.415 537.5316) 
(list 4725.415 537.3546) 
(list 4799.4375 537.2046)))
(apply 'command (append '("pline") coords '("c")))
(setq currobj (ssadd (entlast) currobj))
(setq coords (list 
(list 4799.4375 537.0616) 
(list 4725.415 537.2116) 
(list 4725.415 537.0346) 
(list 4799.4375 536.9846)))
(apply 'command (append '("pline") coords '("c")))
(setq currobj (ssadd (entlast) currobj))
(setq coords (list 
(list 4799.4375 536.8416) 
(list 4725.415 536.8916) 
(list 4725.415 536.7146) 
(list 4799.4375 536.7646)))
(apply 'command (append '("pline") coords '("c")))
(setq currobj (ssadd (entlast) currobj))
(setq coords (list 
(list 4799.4375 536.6216) 
(list 4725.415 536.5716) 
(list 4725.415 536.3946) 
(list 4799.4375 536.5446)))
(apply 'command (append '("pline") coords '("c")))
(setq currobj (ssadd (entlast) currobj))
(setq coords (list 
(list 4799.4375 536.4016) 
(list 4725.415 536.2516) 
(list 4725.415 536.0746) 
(list 4799.4375 536.3246)))
(apply 'command (append '("pline") coords '("c")))
(setq currobj (ssadd (entlast) currobj))
(setq coords (list 
(list 4799.4375 536.1816) 
(list 4725.415 535.9316) 
(list 4725.415 535.7546) 
(list 4799.4375 536.1046)))
(apply 'command (append '("pline") coords '("c")))
(setq currobj (ssadd (entlast) currobj))
(setq coords (list 
(list 4799.4375 535.9616) 
(list 4725.415 535.6116) 
(list 4725.415 535.4346) 
(list 4799.4375 535.8846)))
(apply 'command (append '("pline") coords '("c")))
(setq currobj (ssadd (entlast) currobj))
(setq coords (list 
(list 4799.4375 535.7416) 
(list 4725.415 535.2916) 
(list 4725.415 535.1146) 
(list 4799.4375 535.6646)))
(apply 'command (append '("pline") coords '("c")))
(setq currobj (ssadd (entlast) currobj))
(setq coords (list 
(list 4799.4375 535.5216) 
(list 4725.415 534.9716) 
(list 4725.415 534.7946) 
(list 4799.4375 535.4446)))
(apply 'command (append '("pline") coords '("c")))
(setq currobj (ssadd (entlast) currobj))
(setq coords (list 
(list 4799.4375 535.3016) 
(list 4725.415 534.6516) 
(list 4725.415 534.4746) 
(list 4799.4375 535.2246)))
(apply 'command (append '("pline") coords '("c")))
(setq currobj (ssadd (entlast) currobj))
(command "_layer" "set" "nitride" "")
(command "_layer" "set" "text" "")
(command "_circle" "4799.0625,524.0816" "0.075")
(command "_circle" "4799.0625,524.3816" "0.075")
(command "_circle" "4799.0625,524.6816" "0.075")
(command "_circle" "4799.0625,524.9816" "0.075")
(command "_circle" "4799.0625,525.2816" "0.075")
(command "_circle" "4798.7625,524.0816" "0.075")
(command "_circle" "4798.7625,524.3816" "0.075")
(command "_circle" "4798.7625,524.6816" "0.075")
(command "_circle" "4798.7625,524.9816" "0.075")
(command "_circle" "4798.7625,525.2816" "0.075")
(command "_circle" "4798.4625,524.0816" "0.075")
(command "_circle" "4798.4625,524.3816" "0.075")
(command "_circle" "4798.4625,524.6816" "0.075")
(command "_circle" "4798.4625,524.9816" "0.075")
(command "_circle" "4798.4625,525.2816" "0.075")
(command "_circle" "4798.1625,524.0816" "0.075")
(command "_circle" "4798.1625,524.3816" "0.075")
(command "_circle" "4798.1625,524.6816" "0.075")
(command "_circle" "4798.1625,524.9816" "0.075")
(command "_circle" "4798.1625,525.2816" "0.075")
(command "_circle" "4797.8625,524.0816" "0.075")
(command "_circle" "4797.8625,524.3816" "0.075")
(command "_circle" "4797.8625,524.6816" "0.075")
(command "_circle" "4797.8625,524.9816" "0.075")
(command "_circle" "4797.8625,525.2816" "0.075")
(command "_layer" "set" "nitride" "")
(setq coords (list 
(list 4800.2625 549.5246) 
(list 4800.2625 665.1693) 
(list 4799.7375 665.1693) 
(list 4799.7375 549.5246)))
(apply 'command (append '("pline") coords '("c")))
(setq currobj (ssadd (entlast) currobj))
(command "_layer" "set" "prebias" "")
(command "_rectangle" "4799.7375,549.5246" "4800.2625,665.1693")
(setq currobj (ssadd (entlast) currobj))
(command "_layer" "set" "nitride" "")
(setq coords (list 
(list 4800.2625 665.1693) 
(list 4800.5625 675.1693) 
(list 4800.5625 675.1693) 
(list 4800.5625 676.1693) 
(list 4874.585 675.4193) 
(list 4874.585 680.3623) 
(list 4800.5625 679.6123) 
(list 4800.5625 680.6123) 
(list 4800.5625 680.6123) 
(list 4800.2625 690.6123) 
(list 4799.7375 690.6123) 
(list 4799.4375 680.6123) 
(list 4799.4375 680.6123) 
(list 4799.4375 679.6123) 
(list 4725.415 680.3623) 
(list 4725.415 675.4193) 
(list 4799.4375 676.1693) 
(list 4799.4375 675.1693) 
(list 4799.4375 675.1693) 
(list 4799.7375 665.1693)))
(apply 'command (append '("pline") coords '("c")))
(setq currobj (ssadd (entlast) currobj))
(command "_layer" "set" "prebias" "")
(setq coords (list 
(list 4799.4375 665.1693) 
(list 4799.4375 676.1693) 
(list 4725.415 675.4193) 
(list 4725.415 680.3623) 
(list 4799.4375 679.6123) 
(list 4799.4375 690.6123) 
(list 4800.5625 690.6123) 
(list 4800.5625 679.6123) 
(list 4874.585 680.3623) 
(list 4874.585 675.4193) 
(list 4800.5625 676.1693) 
(list 4800.5625 665.1693)))
(apply 'command (append '("pline") coords '("c")))
(setq currobj (ssadd (entlast) currobj))
(command "_layer" "set" "nitride" "")
(command "_layer" "set" "fda1" "")
(setq coords (list 
(list 4800.5625 676.3123) 
(list 4874.585 675.5623) 
(list 4874.585 675.7393) 
(list 4800.5625 676.3893)))
(apply 'command (append '("pline") coords '("c")))
(setq currobj (ssadd (entlast) currobj))
(setq coords (list 
(list 4800.5625 676.5323) 
(list 4874.585 675.8823) 
(list 4874.585 676.0593) 
(list 4800.5625 676.6093)))
(apply 'command (append '("pline") coords '("c")))
(setq currobj (ssadd (entlast) currobj))
(setq coords (list 
(list 4800.5625 676.7523) 
(list 4874.585 676.2023) 
(list 4874.585 676.3793) 
(list 4800.5625 676.8293)))
(apply 'command (append '("pline") coords '("c")))
(setq currobj (ssadd (entlast) currobj))
(setq coords (list 
(list 4800.5625 676.9723) 
(list 4874.585 676.5223) 
(list 4874.585 676.6993) 
(list 4800.5625 677.0493)))
(apply 'command (append '("pline") coords '("c")))
(setq currobj (ssadd (entlast) currobj))
(setq coords (list 
(list 4800.5625 677.1923) 
(list 4874.585 676.8423) 
(list 4874.585 677.0193) 
(list 4800.5625 677.2693)))
(apply 'command (append '("pline") coords '("c")))
(setq currobj (ssadd (entlast) currobj))
(setq coords (list 
(list 4800.5625 677.4123) 
(list 4874.585 677.1623) 
(list 4874.585 677.3393) 
(list 4800.5625 677.4893)))
(apply 'command (append '("pline") coords '("c")))
(setq currobj (ssadd (entlast) currobj))
(setq coords (list 
(list 4800.5625 677.6323) 
(list 4874.585 677.4823) 
(list 4874.585 677.6593) 
(list 4800.5625 677.7093)))
(apply 'command (append '("pline") coords '("c")))
(setq currobj (ssadd (entlast) currobj))
(setq coords (list 
(list 4800.5625 677.8523) 
(list 4874.585 677.8023) 
(list 4874.585 677.9793) 
(list 4800.5625 677.9293)))
(apply 'command (append '("pline") coords '("c")))
(setq currobj (ssadd (entlast) currobj))
(setq coords (list 
(list 4800.5625 678.0723) 
(list 4874.585 678.1223) 
(list 4874.585 678.2993) 
(list 4800.5625 678.1493)))
(apply 'command (append '("pline") coords '("c")))
(setq currobj (ssadd (entlast) currobj))
(setq coords (list 
(list 4800.5625 678.2923) 
(list 4874.585 678.4423) 
(list 4874.585 678.6193) 
(list 4800.5625 678.3693)))
(apply 'command (append '("pline") coords '("c")))
(setq currobj (ssadd (entlast) currobj))
(setq coords (list 
(list 4800.5625 678.5123) 
(list 4874.585 678.7623) 
(list 4874.585 678.9393) 
(list 4800.5625 678.5893)))
(apply 'command (append '("pline") coords '("c")))
(setq currobj (ssadd (entlast) currobj))
(setq coords (list 
(list 4800.5625 678.7323) 
(list 4874.585 679.0823) 
(list 4874.585 679.2593) 
(list 4800.5625 678.8093)))
(apply 'command (append '("pline") coords '("c")))
(setq currobj (ssadd (entlast) currobj))
(setq coords (list 
(list 4800.5625 678.9523) 
(list 4874.585 679.4023) 
(list 4874.585 679.5793) 
(list 4800.5625 679.0293)))
(apply 'command (append '("pline") coords '("c")))
(setq currobj (ssadd (entlast) currobj))
(setq coords (list 
(list 4800.5625 679.1723) 
(list 4874.585 679.7223) 
(list 4874.585 679.8993) 
(list 4800.5625 679.2493)))
(apply 'command (append '("pline") coords '("c")))
(setq currobj (ssadd (entlast) currobj))
(setq coords (list 
(list 4800.5625 679.3923) 
(list 4874.585 680.0423) 
(list 4874.585 680.2193) 
(list 4800.5625 679.4693)))
(apply 'command (append '("pline") coords '("c")))
(setq currobj (ssadd (entlast) currobj))
(setq coords (list 
(list 4799.4375 679.4693) 
(list 4725.415 680.2193) 
(list 4725.415 680.0423) 
(list 4799.4375 679.3923)))
(apply 'command (append '("pline") coords '("c")))
(setq currobj (ssadd (entlast) currobj))
(setq coords (list 
(list 4799.4375 679.2493) 
(list 4725.415 679.8993) 
(list 4725.415 679.7223) 
(list 4799.4375 679.1723)))
(apply 'command (append '("pline") coords '("c")))
(setq currobj (ssadd (entlast) currobj))
(setq coords (list 
(list 4799.4375 679.0293) 
(list 4725.415 679.5793) 
(list 4725.415 679.4023) 
(list 4799.4375 678.9523)))
(apply 'command (append '("pline") coords '("c")))
(setq currobj (ssadd (entlast) currobj))
(setq coords (list 
(list 4799.4375 678.8093) 
(list 4725.415 679.2593) 
(list 4725.415 679.0823) 
(list 4799.4375 678.7323)))
(apply 'command (append '("pline") coords '("c")))
(setq currobj (ssadd (entlast) currobj))
(setq coords (list 
(list 4799.4375 678.5893) 
(list 4725.415 678.9393) 
(list 4725.415 678.7623) 
(list 4799.4375 678.5123)))
(apply 'command (append '("pline") coords '("c")))
(setq currobj (ssadd (entlast) currobj))
(setq coords (list 
(list 4799.4375 678.3693) 
(list 4725.415 678.6193) 
(list 4725.415 678.4423) 
(list 4799.4375 678.2923)))
(apply 'command (append '("pline") coords '("c")))
(setq currobj (ssadd (entlast) currobj))
(setq coords (list 
(list 4799.4375 678.1493) 
(list 4725.415 678.2993) 
(list 4725.415 678.1223) 
(list 4799.4375 678.0723)))
(apply 'command (append '("pline") coords '("c")))
(setq currobj (ssadd (entlast) currobj))
(setq coords (list 
(list 4799.4375 677.9293) 
(list 4725.415 677.9793) 
(list 4725.415 677.8023) 
(list 4799.4375 677.8523)))
(apply 'command (append '("pline") coords '("c")))
(setq currobj (ssadd (entlast) currobj))
(setq coords (list 
(list 4799.4375 677.7093) 
(list 4725.415 677.6593) 
(list 4725.415 677.4823) 
(list 4799.4375 677.6323)))
(apply 'command (append '("pline") coords '("c")))
(setq currobj (ssadd (entlast) currobj))
(setq coords (list 
(list 4799.4375 677.4893) 
(list 4725.415 677.3393) 
(list 4725.415 677.1623) 
(list 4799.4375 677.4123)))
(apply 'command (append '("pline") coords '("c")))
(setq currobj (ssadd (entlast) currobj))
(setq coords (list 
(list 4799.4375 677.2693) 
(list 4725.415 677.0193) 
(list 4725.415 676.8423) 
(list 4799.4375 677.1923)))
(apply 'command (append '("pline") coords '("c")))
(setq currobj (ssadd (entlast) currobj))
(setq coords (list 
(list 4799.4375 677.0493) 
(list 4725.415 676.6993) 
(list 4725.415 676.5223) 
(list 4799.4375 676.9723)))
(apply 'command (append '("pline") coords '("c")))
(setq currobj (ssadd (entlast) currobj))
(setq coords (list 
(list 4799.4375 676.8293) 
(list 4725.415 676.3793) 
(list 4725.415 676.2023) 
(list 4799.4375 676.7523)))
(apply 'command (append '("pline") coords '("c")))
(setq currobj (ssadd (entlast) currobj))
(setq coords (list 
(list 4799.4375 676.6093) 
(list 4725.415 676.0593) 
(list 4725.415 675.8823) 
(list 4799.4375 676.5323)))
(apply 'command (append '("pline") coords '("c")))
(setq currobj (ssadd (entlast) currobj))
(setq coords (list 
(list 4799.4375 676.3893) 
(list 4725.415 675.7393) 
(list 4725.415 675.5623) 
(list 4799.4375 676.3123)))
(apply 'command (append '("pline") coords '("c")))
(setq currobj (ssadd (entlast) currobj))
(command "_layer" "set" "nitride" "")
(command "_layer" "set" "text" "")
(command "_circle" "4799.0625,665.1693" "0.075")
(command "_circle" "4799.0625,665.4693" "0.075")
(command "_circle" "4799.0625,665.7693" "0.075")
(command "_circle" "4799.0625,666.0693" "0.075")
(command "_circle" "4799.0625,666.3693" "0.075")
(command "_circle" "4798.7625,665.1693" "0.075")
(command "_circle" "4798.7625,665.4693" "0.075")
(command "_circle" "4798.7625,665.7693" "0.075")
(command "_circle" "4798.7625,666.0693" "0.075")
(command "_circle" "4798.7625,666.3693" "0.075")
(command "_circle" "4798.4625,665.1693" "0.075")
(command "_circle" "4798.4625,665.4693" "0.075")
(command "_circle" "4798.4625,665.7693" "0.075")
(command "_circle" "4798.4625,666.0693" "0.075")
(command "_circle" "4798.4625,666.3693" "0.075")
(command "_circle" "4798.1625,665.1693" "0.075")
(command "_circle" "4798.1625,665.4693" "0.075")
(command "_circle" "4798.1625,665.7693" "0.075")
(command "_circle" "4798.1625,666.0693" "0.075")
(command "_circle" "4798.1625,666.3693" "0.075")
(command "_circle" "4797.8625,665.1693" "0.075")
(command "_circle" "4797.8625,665.4693" "0.075")
(command "_circle" "4797.8625,665.7693" "0.075")
(command "_circle" "4797.8625,666.0693" "0.075")
(command "_circle" "4797.8625,666.3693" "0.075")
(command "_layer" "set" "nitride" "")
(setq coords (list 
(list 4800.2625 690.6123) 
(list 4800.2625 806.257) 
(list 4799.7375 806.257) 
(list 4799.7375 690.6123)))
(apply 'command (append '("pline") coords '("c")))
(setq currobj (ssadd (entlast) currobj))
(command "_layer" "set" "prebias" "")
(command "_rectangle" "4799.7375,690.6123" "4800.2625,806.257")
(setq currobj (ssadd (entlast) currobj))
(command "_layer" "set" "nitride" "")
(setq coords (list 
(list 4800.2625 806.257) 
(list 4800.5625 816.257) 
(list 4800.5625 816.257) 
(list 4800.5625 817.257) 
(list 4874.585 816.507) 
(list 4874.585 821.45) 
(list 4800.5625 820.7) 
(list 4800.5625 821.7) 
(list 4800.5625 821.7) 
(list 4800.2625 831.7) 
(list 4799.7375 831.7) 
(list 4799.4375 821.7) 
(list 4799.4375 821.7) 
(list 4799.4375 820.7) 
(list 4725.415 821.45) 
(list 4725.415 816.507) 
(list 4799.4375 817.257) 
(list 4799.4375 816.257) 
(list 4799.4375 816.257) 
(list 4799.7375 806.257)))
(apply 'command (append '("pline") coords '("c")))
(setq currobj (ssadd (entlast) currobj))
(command "_layer" "set" "prebias" "")
(setq coords (list 
(list 4799.4375 806.257) 
(list 4799.4375 817.257) 
(list 4725.415 816.507) 
(list 4725.415 821.45) 
(list 4799.4375 820.7) 
(list 4799.4375 831.7) 
(list 4800.5625 831.7) 
(list 4800.5625 820.7) 
(list 4874.585 821.45) 
(list 4874.585 816.507) 
(list 4800.5625 817.257) 
(list 4800.5625 806.257)))
(apply 'command (append '("pline") coords '("c")))
(setq currobj (ssadd (entlast) currobj))
(command "_layer" "set" "nitride" "")
(command "_layer" "set" "fda1" "")
(setq coords (list 
(list 4800.5625 817.4) 
(list 4874.585 816.65) 
(list 4874.585 816.827) 
(list 4800.5625 817.477)))
(apply 'command (append '("pline") coords '("c")))
(setq currobj (ssadd (entlast) currobj))
(setq coords (list 
(list 4800.5625 817.62) 
(list 4874.585 816.97) 
(list 4874.585 817.147) 
(list 4800.5625 817.697)))
(apply 'command (append '("pline") coords '("c")))
(setq currobj (ssadd (entlast) currobj))
(setq coords (list 
(list 4800.5625 817.84) 
(list 4874.585 817.29) 
(list 4874.585 817.467) 
(list 4800.5625 817.917)))
(apply 'command (append '("pline") coords '("c")))
(setq currobj (ssadd (entlast) currobj))
(setq coords (list 
(list 4800.5625 818.06) 
(list 4874.585 817.61) 
(list 4874.585 817.787) 
(list 4800.5625 818.137)))
(apply 'command (append '("pline") coords '("c")))
(setq currobj (ssadd (entlast) currobj))
(setq coords (list 
(list 4800.5625 818.28) 
(list 4874.585 817.93) 
(list 4874.585 818.107) 
(list 4800.5625 818.357)))
(apply 'command (append '("pline") coords '("c")))
(setq currobj (ssadd (entlast) currobj))
(setq coords (list 
(list 4800.5625 818.5) 
(list 4874.585 818.25) 
(list 4874.585 818.427) 
(list 4800.5625 818.577)))
(apply 'command (append '("pline") coords '("c")))
(setq currobj (ssadd (entlast) currobj))
(setq coords (list 
(list 4800.5625 818.72) 
(list 4874.585 818.57) 
(list 4874.585 818.747) 
(list 4800.5625 818.797)))
(apply 'command (append '("pline") coords '("c")))
(setq currobj (ssadd (entlast) currobj))
(setq coords (list 
(list 4800.5625 818.94) 
(list 4874.585 818.89) 
(list 4874.585 819.067) 
(list 4800.5625 819.017)))
(apply 'command (append '("pline") coords '("c")))
(setq currobj (ssadd (entlast) currobj))
(setq coords (list 
(list 4800.5625 819.16) 
(list 4874.585 819.21) 
(list 4874.585 819.387) 
(list 4800.5625 819.237)))
(apply 'command (append '("pline") coords '("c")))
(setq currobj (ssadd (entlast) currobj))
(setq coords (list 
(list 4800.5625 819.38) 
(list 4874.585 819.53) 
(list 4874.585 819.707) 
(list 4800.5625 819.457)))
(apply 'command (append '("pline") coords '("c")))
(setq currobj (ssadd (entlast) currobj))
(setq coords (list 
(list 4800.5625 819.6) 
(list 4874.585 819.85) 
(list 4874.585 820.027) 
(list 4800.5625 819.677)))
(apply 'command (append '("pline") coords '("c")))
(setq currobj (ssadd (entlast) currobj))
(setq coords (list 
(list 4800.5625 819.82) 
(list 4874.585 820.17) 
(list 4874.585 820.347) 
(list 4800.5625 819.897)))
(apply 'command (append '("pline") coords '("c")))
(setq currobj (ssadd (entlast) currobj))
(setq coords (list 
(list 4800.5625 820.04) 
(list 4874.585 820.49) 
(list 4874.585 820.667) 
(list 4800.5625 820.117)))
(apply 'command (append '("pline") coords '("c")))
(setq currobj (ssadd (entlast) currobj))
(setq coords (list 
(list 4800.5625 820.26) 
(list 4874.585 820.81) 
(list 4874.585 820.987) 
(list 4800.5625 820.337)))
(apply 'command (append '("pline") coords '("c")))
(setq currobj (ssadd (entlast) currobj))
(setq coords (list 
(list 4800.5625 820.48) 
(list 4874.585 821.13) 
(list 4874.585 821.307) 
(list 4800.5625 820.557)))
(apply 'command (append '("pline") coords '("c")))
(setq currobj (ssadd (entlast) currobj))
(setq coords (list 
(list 4799.4375 820.557) 
(list 4725.415 821.307) 
(list 4725.415 821.13) 
(list 4799.4375 820.48)))
(apply 'command (append '("pline") coords '("c")))
(setq currobj (ssadd (entlast) currobj))
(setq coords (list 
(list 4799.4375 820.337) 
(list 4725.415 820.987) 
(list 4725.415 820.81) 
(list 4799.4375 820.26)))
(apply 'command (append '("pline") coords '("c")))
(setq currobj (ssadd (entlast) currobj))
(setq coords (list 
(list 4799.4375 820.117) 
(list 4725.415 820.667) 
(list 4725.415 820.49) 
(list 4799.4375 820.04)))
(apply 'command (append '("pline") coords '("c")))
(setq currobj (ssadd (entlast) currobj))
(setq coords (list 
(list 4799.4375 819.897) 
(list 4725.415 820.347) 
(list 4725.415 820.17) 
(list 4799.4375 819.82)))
(apply 'command (append '("pline") coords '("c")))
(setq currobj (ssadd (entlast) currobj))
(setq coords (list 
(list 4799.4375 819.677) 
(list 4725.415 820.027) 
(list 4725.415 819.85) 
(list 4799.4375 819.6)))
(apply 'command (append '("pline") coords '("c")))
(setq currobj (ssadd (entlast) currobj))
(setq coords (list 
(list 4799.4375 819.457) 
(list 4725.415 819.707) 
(list 4725.415 819.53) 
(list 4799.4375 819.38)))
(apply 'command (append '("pline") coords '("c")))
(setq currobj (ssadd (entlast) currobj))
(setq coords (list 
(list 4799.4375 819.237) 
(list 4725.415 819.387) 
(list 4725.415 819.21) 
(list 4799.4375 819.16)))
(apply 'command (append '("pline") coords '("c")))
(setq currobj (ssadd (entlast) currobj))
(setq coords (list 
(list 4799.4375 819.017) 
(list 4725.415 819.067) 
(list 4725.415 818.89) 
(list 4799.4375 818.94)))
(apply 'command (append '("pline") coords '("c")))
(setq currobj (ssadd (entlast) currobj))
(setq coords (list 
(list 4799.4375 818.797) 
(list 4725.415 818.747) 
(list 4725.415 818.57) 
(list 4799.4375 818.72)))
(apply 'command (append '("pline") coords '("c")))
(setq currobj (ssadd (entlast) currobj))
(setq coords (list 
(list 4799.4375 818.577) 
(list 4725.415 818.427) 
(list 4725.415 818.25) 
(list 4799.4375 818.5)))
(apply 'command (append '("pline") coords '("c")))
(setq currobj (ssadd (entlast) currobj))
(setq coords (list 
(list 4799.4375 818.357) 
(list 4725.415 818.107) 
(list 4725.415 817.93) 
(list 4799.4375 818.28)))
(apply 'command (append '("pline") coords '("c")))
(setq currobj (ssadd (entlast) currobj))
(setq coords (list 
(list 4799.4375 818.137) 
(list 4725.415 817.787) 
(list 4725.415 817.61) 
(list 4799.4375 818.06)))
(apply 'command (append '("pline") coords '("c")))
(setq currobj (ssadd (entlast) currobj))
(setq coords (list 
(list 4799.4375 817.917) 
(list 4725.415 817.467) 
(list 4725.415 817.29) 
(list 4799.4375 817.84)))
(apply 'command (append '("pline") coords '("c")))
(setq currobj (ssadd (entlast) currobj))
(setq coords (list 
(list 4799.4375 817.697) 
(list 4725.415 817.147) 
(list 4725.415 816.97) 
(list 4799.4375 817.62)))
(apply 'command (append '("pline") coords '("c")))
(setq currobj (ssadd (entlast) currobj))
(setq coords (list 
(list 4799.4375 817.477) 
(list 4725.415 816.827) 
(list 4725.415 816.65) 
(list 4799.4375 817.4)))
(apply 'command (append '("pline") coords '("c")))
(setq currobj (ssadd (entlast) currobj))
(command "_layer" "set" "nitride" "")
(command "_layer" "set" "text" "")
(command "_circle" "4799.0625,806.257" "0.075")
(command "_circle" "4799.0625,806.557" "0.075")
(command "_circle" "4799.0625,806.857" "0.075")
(command "_circle" "4799.0625,807.157" "0.075")
(command "_circle" "4799.0625,807.457" "0.075")
(command "_circle" "4798.7625,806.257" "0.075")
(command "_circle" "4798.7625,806.557" "0.075")
(command "_circle" "4798.7625,806.857" "0.075")
(command "_circle" "4798.7625,807.157" "0.075")
(command "_circle" "4798.7625,807.457" "0.075")
(command "_circle" "4798.4625,806.257" "0.075")
(command "_circle" "4798.4625,806.557" "0.075")
(command "_circle" "4798.4625,806.857" "0.075")
(command "_circle" "4798.4625,807.157" "0.075")
(command "_circle" "4798.4625,807.457" "0.075")
(command "_circle" "4798.1625,806.257" "0.075")
(command "_circle" "4798.1625,806.557" "0.075")
(command "_circle" "4798.1625,806.857" "0.075")
(command "_circle" "4798.1625,807.157" "0.075")
(command "_circle" "4798.1625,807.457" "0.075")
(command "_circle" "4797.8625,806.257" "0.075")
(command "_circle" "4797.8625,806.557" "0.075")
(command "_circle" "4797.8625,806.857" "0.075")
(command "_circle" "4797.8625,807.157" "0.075")
(command "_circle" "4797.8625,807.457" "0.075")
(command "_layer" "set" "nitride" "")
(setq coords (list 
(list 4800.2625 831.7) 
(list 4800.2625 836.7) 
(list 4799.7375 836.7) 
(list 4799.7375 831.7)))
(apply 'command (append '("pline") coords '("c")))
(setq currobj (ssadd (entlast) currobj))
(command "_layer" "set" "prebias" "")
(command "_rectangle" "4799.7375,831.7" "4800.2625,836.7")
(setq currobj (ssadd (entlast) currobj))
(command "_layer" "set" "nitride" "")
(setq cooledsinglenanobeam15 currobj)
(setq currobj nil)
(setq currobj (ssadd))
; DRAWING PHOTONIC CRYSTAL
(command "_layer" "set" "negYjunc" "")
(setq coords (list 
(list 4800.135 866.7) 
(list 4800 851.7) 
(list 4800 866.7)))
(apply 'command (append '("pline") coords '("c")))
(setq currobj (ssadd (entlast) currobj))
(setq coords (list 
(list 4800.2625 836.7) 
(list 4800.415 866.7) 
(list 4801.136 866.7) 
(list 4801.136 836.7)))
(apply 'command (append '("pline") coords '("c")))
(setq currobj (ssadd (entlast) currobj))
(setq coords (list 
(list 4799.865 866.7) 
(list 4800 851.7) 
(list 4800 866.7)))
(apply 'command (append '("pline") coords '("c")))
(setq currobj (ssadd (entlast) currobj))
(setq coords (list 
(list 4799.7375 836.7) 
(list 4799.585 866.7) 
(list 4798.864 866.7) 
(list 4798.864 836.7)))
(apply 'command (append '("pline") coords '("c")))
(setq currobj (ssadd (entlast) currobj))
(command "_layer" "set" "nitride" "")
(setq yjunction15 currobj)
(setq currobj nil)
(setq currobj (ssadd))
(setq tap15 nil)
(setq tap15 (ssadd))
(command "_layer" "set" "phc" "")
(setq coords (list 
(list 4800 866.7) 
(list 4800.135 866.7) 
(list 4800.135 866.7103) 
(list 4800.135 866.7206) 
(list 4800.135 866.7308) 
(list 4800.135 866.7411) 
(list 4800.135 866.7514) 
(list 4800.135 866.7617) 
(list 4800.135 866.7719) 
(list 4800.135 866.7822) 
(list 4800.135 866.7925) 
(list 4800.135 866.8028) 
(list 4800.135 866.8131) 
(list 4800.135 866.8233) 
(list 4800.135 866.8336) 
(list 4800.135 866.8439) 
(list 4800.135 866.8542) 
(list 4800.135 866.8644) 
(list 4800.135 866.8747) 
(list 4800.135 866.885) 
(list 4800.135 866.8953) 
(list 4800.135 866.9056) 
(list 4800.135 866.9158) 
(list 4800.135 866.9261) 
(list 4800.135 866.9364) 
(list 4800.135 866.9467) 
(list 4800.135 866.9569) 
(list 4800.135 866.9672) 
(list 4800.135 866.9775) 
(list 4800.135 866.9878) 
(list 4800.135 866.9981) 
(list 4800.135 867.0083) 
(list 4800.135 867.0186) 
(list 4800.135 867.0289) 
(list 4800.135 867.0392) 
(list 4800.135 867.0494) 
(list 4800.135 867.0597) 
(list 4800.135 867.07) 
(list 4800 867.07)))
(apply 'command (append '("pline") coords '("c")))
(setq tap15 (ssadd (entlast) tap15))
(command "_mirror" (entlast) "" "4800,900" "4800,901" "No")
(setq tap15 (ssadd (entlast) tap15))
(setq coords (list 
(list 4800.4252 866.7) 
(list 4800.415 866.7) 
(list 4800.4153 866.7103) 
(list 4800.4155 866.7206) 
(list 4800.4158 866.7308) 
(list 4800.4159 866.7411) 
(list 4800.416 866.7514) 
(list 4800.4159 866.7617) 
(list 4800.4158 866.7719) 
(list 4800.4156 866.7822) 
(list 4800.4153 866.7925) 
(list 4800.4149 866.8028) 
(list 4800.4144 866.8131) 
(list 4800.4139 866.8233) 
(list 4800.4133 866.8336) 
(list 4800.4128 866.8439) 
(list 4800.4123 866.8542) 
(list 4800.4118 866.8644) 
(list 4800.4114 866.8747) 
(list 4800.4111 866.885) 
(list 4800.411 866.8953) 
(list 4800.411 866.9056) 
(list 4800.4112 866.9158) 
(list 4800.4115 866.9261) 
(list 4800.4121 866.9364) 
(list 4800.4128 866.9467) 
(list 4800.4137 866.9569) 
(list 4800.4147 866.9672) 
(list 4800.4159 866.9775) 
(list 4800.4171 866.9878) 
(list 4800.4184 866.9981) 
(list 4800.4198 867.0083) 
(list 4800.421 867.0186) 
(list 4800.4222 867.0289) 
(list 4800.4232 867.0392) 
(list 4800.4241 867.0494) 
(list 4800.4248 867.0597) 
(list 4800.4252 867.07) 
(list 4800.4252 867.07)))
(apply 'command (append '("pline") coords '("c")))
(setq tap15 (ssadd (entlast) tap15))
(command "_mirror" (entlast) "" "4800,900" "4800,901" "No")
(setq tap15 (ssadd (entlast) tap15))
(setq coords (list 
(list 4801.136 866.7) 
(list 4800.4252 866.7) 
(list 4800.4252 866.7103) 
(list 4800.4252 866.7206) 
(list 4800.4252 866.7308) 
(list 4800.4252 866.7411) 
(list 4800.4252 866.7514) 
(list 4800.4252 866.7617) 
(list 4800.4252 866.7719) 
(list 4800.4252 866.7822) 
(list 4800.4252 866.7925) 
(list 4800.4252 866.8028) 
(list 4800.4252 866.8131) 
(list 4800.4252 866.8233) 
(list 4800.4252 866.8336) 
(list 4800.4252 866.8439) 
(list 4800.4252 866.8542) 
(list 4800.4252 866.8644) 
(list 4800.4252 866.8747) 
(list 4800.4252 866.885) 
(list 4800.4252 866.8953) 
(list 4800.4252 866.9056) 
(list 4800.4252 866.9158) 
(list 4800.4252 866.9261) 
(list 4800.4252 866.9364) 
(list 4800.4252 866.9467) 
(list 4800.4252 866.9569) 
(list 4800.4252 866.9672) 
(list 4800.4252 866.9775) 
(list 4800.4252 866.9878) 
(list 4800.4252 866.9981) 
(list 4800.4252 867.0083) 
(list 4800.4252 867.0186) 
(list 4800.4252 867.0289) 
(list 4800.4252 867.0392) 
(list 4800.4252 867.0494) 
(list 4800.4252 867.0597) 
(list 4800.4252 867.07) 
(list 4801.136 867.07)))
(apply 'command (append '("pline") coords '("c")))
(setq tap15 (ssadd (entlast) tap15))
(command "_mirror" (entlast) "" "4800,900" "4800,901" "No")
(setq tap15 (ssadd (entlast) tap15))
(setq coords (list 
(list 4800 867.07) 
(list 4800.135 867.07) 
(list 4800.135 867.0803) 
(list 4800.135 867.0906) 
(list 4800.135 867.1008) 
(list 4800.135 867.1111) 
(list 4800.135 867.1214) 
(list 4800.135 867.1317) 
(list 4800.135 867.1419) 
(list 4800.135 867.1522) 
(list 4800.135 867.1625) 
(list 4800.135 867.1728) 
(list 4800.135 867.1831) 
(list 4800.135 867.1933) 
(list 4800.135 867.2036) 
(list 4800.135 867.2139) 
(list 4800.135 867.2242) 
(list 4800.135 867.2344) 
(list 4800.135 867.2447) 
(list 4800.135 867.255) 
(list 4800.135 867.2653) 
(list 4800.135 867.2756) 
(list 4800.135 867.2858) 
(list 4800.135 867.2961) 
(list 4800.135 867.3064) 
(list 4800.135 867.3167) 
(list 4800.135 867.3269) 
(list 4800.135 867.3372) 
(list 4800.135 867.3475) 
(list 4800.135 867.3578) 
(list 4800.135 867.3681) 
(list 4800.135 867.3783) 
(list 4800.135 867.3886) 
(list 4800.135 867.3989) 
(list 4800.135 867.4092) 
(list 4800.135 867.4194) 
(list 4800.135 867.4297) 
(list 4800.135 867.44) 
(list 4800 867.44)))
(apply 'command (append '("pline") coords '("c")))
(setq tap15 (ssadd (entlast) tap15))
(command "_mirror" (entlast) "" "4800,900" "4800,901" "No")
(setq tap15 (ssadd (entlast) tap15))
(setq coords (list 
(list 4800.4354 867.07) 
(list 4800.4252 867.07) 
(list 4800.4253 867.0803) 
(list 4800.4252 867.0906) 
(list 4800.4247 867.1008) 
(list 4800.424 867.1111) 
(list 4800.423 867.1214) 
(list 4800.4217 867.1317) 
(list 4800.4201 867.1419) 
(list 4800.4184 867.1522) 
(list 4800.4165 867.1625) 
(list 4800.4145 867.1728) 
(list 4800.4125 867.1831) 
(list 4800.4106 867.1933) 
(list 4800.4088 867.2036) 
(list 4800.4071 867.2139) 
(list 4800.4057 867.2242) 
(list 4800.4045 867.2344) 
(list 4800.4037 867.2447) 
(list 4800.4033 867.255) 
(list 4800.4033 867.2653) 
(list 4800.4037 867.2756) 
(list 4800.4046 867.2858) 
(list 4800.4058 867.2961) 
(list 4800.4075 867.3064) 
(list 4800.4095 867.3167) 
(list 4800.4118 867.3269) 
(list 4800.4144 867.3372) 
(list 4800.4171 867.3475) 
(list 4800.4199 867.3578) 
(list 4800.4227 867.3681) 
(list 4800.4254 867.3783) 
(list 4800.428 867.3886) 
(list 4800.4303 867.3989) 
(list 4800.4322 867.4092) 
(list 4800.4338 867.4194) 
(list 4800.4348 867.4297) 
(list 4800.4354 867.44) 
(list 4800.4354 867.44)))
(apply 'command (append '("pline") coords '("c")))
(setq tap15 (ssadd (entlast) tap15))
(command "_mirror" (entlast) "" "4800,900" "4800,901" "No")
(setq tap15 (ssadd (entlast) tap15))
(setq coords (list 
(list 4801.136 867.07) 
(list 4800.4354 867.07) 
(list 4800.4354 867.0803) 
(list 4800.4354 867.0906) 
(list 4800.4354 867.1008) 
(list 4800.4354 867.1111) 
(list 4800.4354 867.1214) 
(list 4800.4354 867.1317) 
(list 4800.4354 867.1419) 
(list 4800.4354 867.1522) 
(list 4800.4354 867.1625) 
(list 4800.4354 867.1728) 
(list 4800.4354 867.1831) 
(list 4800.4354 867.1933) 
(list 4800.4354 867.2036) 
(list 4800.4354 867.2139) 
(list 4800.4354 867.2242) 
(list 4800.4354 867.2344) 
(list 4800.4354 867.2447) 
(list 4800.4354 867.255) 
(list 4800.4354 867.2653) 
(list 4800.4354 867.2756) 
(list 4800.4354 867.2858) 
(list 4800.4354 867.2961) 
(list 4800.4354 867.3064) 
(list 4800.4354 867.3167) 
(list 4800.4354 867.3269) 
(list 4800.4354 867.3372) 
(list 4800.4354 867.3475) 
(list 4800.4354 867.3578) 
(list 4800.4354 867.3681) 
(list 4800.4354 867.3783) 
(list 4800.4354 867.3886) 
(list 4800.4354 867.3989) 
(list 4800.4354 867.4092) 
(list 4800.4354 867.4194) 
(list 4800.4354 867.4297) 
(list 4800.4354 867.44) 
(list 4801.136 867.44)))
(apply 'command (append '("pline") coords '("c")))
(setq tap15 (ssadd (entlast) tap15))
(command "_mirror" (entlast) "" "4800,900" "4800,901" "No")
(setq tap15 (ssadd (entlast) tap15))
(setq coords (list 
(list 4800 867.44) 
(list 4800.135 867.44) 
(list 4800.135 867.4503) 
(list 4800.135 867.4606) 
(list 4800.135 867.4708) 
(list 4800.135 867.4811) 
(list 4800.135 867.4914) 
(list 4800.135 867.5017) 
(list 4800.135 867.5119) 
(list 4800.135 867.5222) 
(list 4800.135 867.5325) 
(list 4800.135 867.5428) 
(list 4800.135 867.5531) 
(list 4800.135 867.5633) 
(list 4800.135 867.5736) 
(list 4800.135 867.5839) 
(list 4800.135 867.5942) 
(list 4800.135 867.6044) 
(list 4800.135 867.6147) 
(list 4800.135 867.625) 
(list 4800.135 867.6353) 
(list 4800.135 867.6456) 
(list 4800.135 867.6558) 
(list 4800.135 867.6661) 
(list 4800.135 867.6764) 
(list 4800.135 867.6867) 
(list 4800.135 867.6969) 
(list 4800.135 867.7072) 
(list 4800.135 867.7175) 
(list 4800.135 867.7278) 
(list 4800.135 867.7381) 
(list 4800.135 867.7483) 
(list 4800.135 867.7586) 
(list 4800.135 867.7689) 
(list 4800.135 867.7792) 
(list 4800.135 867.7894) 
(list 4800.135 867.7997) 
(list 4800.135 867.81) 
(list 4800 867.81)))
(apply 'command (append '("pline") coords '("c")))
(setq tap15 (ssadd (entlast) tap15))
(command "_mirror" (entlast) "" "4800,900" "4800,901" "No")
(setq tap15 (ssadd (entlast) tap15))
(setq coords (list 
(list 4800.4456 867.44) 
(list 4800.4354 867.44) 
(list 4800.4354 867.4503) 
(list 4800.4349 867.4606) 
(list 4800.4337 867.4708) 
(list 4800.4321 867.4811) 
(list 4800.4299 867.4914) 
(list 4800.4273 867.5017) 
(list 4800.4244 867.5119) 
(list 4800.4211 867.5222) 
(list 4800.4177 867.5325) 
(list 4800.4142 867.5428) 
(list 4800.4107 867.5531) 
(list 4800.4073 867.5633) 
(list 4800.4042 867.5736) 
(list 4800.4014 867.5839) 
(list 4800.3991 867.5942) 
(list 4800.3973 867.6044) 
(list 4800.3961 867.6147) 
(list 4800.3955 867.625) 
(list 4800.3956 867.6353) 
(list 4800.3965 867.6456) 
(list 4800.398 867.6558) 
(list 4800.4001 867.6661) 
(list 4800.4029 867.6764) 
(list 4800.4062 867.6867) 
(list 4800.4099 867.6969) 
(list 4800.414 867.7072) 
(list 4800.4183 867.7175) 
(list 4800.4227 867.7278) 
(list 4800.427 867.7381) 
(list 4800.4312 867.7483) 
(list 4800.435 867.7586) 
(list 4800.4384 867.7689) 
(list 4800.4412 867.7792) 
(list 4800.4434 867.7894) 
(list 4800.4449 867.7997) 
(list 4800.4456 867.81) 
(list 4800.4456 867.81)))
(apply 'command (append '("pline") coords '("c")))
(setq tap15 (ssadd (entlast) tap15))
(command "_mirror" (entlast) "" "4800,900" "4800,901" "No")
(setq tap15 (ssadd (entlast) tap15))
(setq coords (list 
(list 4801.136 867.44) 
(list 4800.4456 867.44) 
(list 4800.4456 867.4503) 
(list 4800.4456 867.4606) 
(list 4800.4456 867.4708) 
(list 4800.4456 867.4811) 
(list 4800.4456 867.4914) 
(list 4800.4456 867.5017) 
(list 4800.4456 867.5119) 
(list 4800.4456 867.5222) 
(list 4800.4456 867.5325) 
(list 4800.4456 867.5428) 
(list 4800.4456 867.5531) 
(list 4800.4456 867.5633) 
(list 4800.4456 867.5736) 
(list 4800.4456 867.5839) 
(list 4800.4456 867.5942) 
(list 4800.4456 867.6044) 
(list 4800.4456 867.6147) 
(list 4800.4456 867.625) 
(list 4800.4456 867.6353) 
(list 4800.4456 867.6456) 
(list 4800.4456 867.6558) 
(list 4800.4456 867.6661) 
(list 4800.4456 867.6764) 
(list 4800.4456 867.6867) 
(list 4800.4456 867.6969) 
(list 4800.4456 867.7072) 
(list 4800.4456 867.7175) 
(list 4800.4456 867.7278) 
(list 4800.4456 867.7381) 
(list 4800.4456 867.7483) 
(list 4800.4456 867.7586) 
(list 4800.4456 867.7689) 
(list 4800.4456 867.7792) 
(list 4800.4456 867.7894) 
(list 4800.4456 867.7997) 
(list 4800.4456 867.81) 
(list 4801.136 867.81)))
(apply 'command (append '("pline") coords '("c")))
(setq tap15 (ssadd (entlast) tap15))
(command "_mirror" (entlast) "" "4800,900" "4800,901" "No")
(setq tap15 (ssadd (entlast) tap15))
(setq coords (list 
(list 4800 867.81) 
(list 4800.135 867.81) 
(list 4800.135 867.8203) 
(list 4800.135 867.8306) 
(list 4800.135 867.8408) 
(list 4800.135 867.8511) 
(list 4800.135 867.8614) 
(list 4800.135 867.8717) 
(list 4800.135 867.8819) 
(list 4800.135 867.8922) 
(list 4800.135 867.9025) 
(list 4800.135 867.9128) 
(list 4800.135 867.9231) 
(list 4800.135 867.9333) 
(list 4800.135 867.9436) 
(list 4800.135 867.9539) 
(list 4800.135 867.9642) 
(list 4800.135 867.9744) 
(list 4800.135 867.9847) 
(list 4800.135 867.995) 
(list 4800.135 868.0053) 
(list 4800.135 868.0156) 
(list 4800.135 868.0258) 
(list 4800.135 868.0361) 
(list 4800.135 868.0464) 
(list 4800.135 868.0567) 
(list 4800.135 868.0669) 
(list 4800.135 868.0772) 
(list 4800.135 868.0875) 
(list 4800.135 868.0978) 
(list 4800.135 868.1081) 
(list 4800.135 868.1183) 
(list 4800.135 868.1286) 
(list 4800.135 868.1389) 
(list 4800.135 868.1492) 
(list 4800.135 868.1594) 
(list 4800.135 868.1697) 
(list 4800.135 868.18) 
(list 4800 868.18)))
(apply 'command (append '("pline") coords '("c")))
(setq tap15 (ssadd (entlast) tap15))
(command "_mirror" (entlast) "" "4800,900" "4800,901" "No")
(setq tap15 (ssadd (entlast) tap15))
(setq coords (list 
(list 4800.4558 867.81) 
(list 4800.4456 867.81) 
(list 4800.4455 867.8203) 
(list 4800.4445 867.8306) 
(list 4800.4427 867.8408) 
(list 4800.4402 867.8511) 
(list 4800.4369 867.8614) 
(list 4800.433 867.8717) 
(list 4800.4287 867.8819) 
(list 4800.4239 867.8922) 
(list 4800.4189 867.9025) 
(list 4800.4138 867.9128) 
(list 4800.4088 867.9231) 
(list 4800.404 867.9333) 
(list 4800.3996 867.9436) 
(list 4800.3957 867.9539) 
(list 4800.3925 867.9642) 
(list 4800.39 867.9744) 
(list 4800.3884 867.9847) 
(list 4800.3877 867.995) 
(list 4800.388 868.0053) 
(list 4800.3892 868.0156) 
(list 4800.3914 868.0258) 
(list 4800.3944 868.0361) 
(list 4800.3983 868.0464) 
(list 4800.4029 868.0567) 
(list 4800.4081 868.0669) 
(list 4800.4136 868.0772) 
(list 4800.4195 868.0875) 
(list 4800.4254 868.0978) 
(list 4800.4313 868.1081) 
(list 4800.4369 868.1183) 
(list 4800.442 868.1286) 
(list 4800.4465 868.1389) 
(list 4800.4502 868.1492) 
(list 4800.4531 868.1594) 
(list 4800.455 868.1697) 
(list 4800.4558 868.18) 
(list 4800.4558 868.18)))
(apply 'command (append '("pline") coords '("c")))
(setq tap15 (ssadd (entlast) tap15))
(command "_mirror" (entlast) "" "4800,900" "4800,901" "No")
(setq tap15 (ssadd (entlast) tap15))
(setq coords (list 
(list 4801.136 867.81) 
(list 4800.4558 867.81) 
(list 4800.4558 867.8203) 
(list 4800.4558 867.8306) 
(list 4800.4558 867.8408) 
(list 4800.4558 867.8511) 
(list 4800.4558 867.8614) 
(list 4800.4558 867.8717) 
(list 4800.4558 867.8819) 
(list 4800.4558 867.8922) 
(list 4800.4558 867.9025) 
(list 4800.4558 867.9128) 
(list 4800.4558 867.9231) 
(list 4800.4558 867.9333) 
(list 4800.4558 867.9436) 
(list 4800.4558 867.9539) 
(list 4800.4558 867.9642) 
(list 4800.4558 867.9744) 
(list 4800.4558 867.9847) 
(list 4800.4558 867.995) 
(list 4800.4558 868.0053) 
(list 4800.4558 868.0156) 
(list 4800.4558 868.0258) 
(list 4800.4558 868.0361) 
(list 4800.4558 868.0464) 
(list 4800.4558 868.0567) 
(list 4800.4558 868.0669) 
(list 4800.4558 868.0772) 
(list 4800.4558 868.0875) 
(list 4800.4558 868.0978) 
(list 4800.4558 868.1081) 
(list 4800.4558 868.1183) 
(list 4800.4558 868.1286) 
(list 4800.4558 868.1389) 
(list 4800.4558 868.1492) 
(list 4800.4558 868.1594) 
(list 4800.4558 868.1697) 
(list 4800.4558 868.18) 
(list 4801.136 868.18)))
(apply 'command (append '("pline") coords '("c")))
(setq tap15 (ssadd (entlast) tap15))
(command "_mirror" (entlast) "" "4800,900" "4800,901" "No")
(setq tap15 (ssadd (entlast) tap15))
(setq coords (list 
(list 4800 868.18) 
(list 4800.135 868.18) 
(list 4800.135 868.1903) 
(list 4800.135 868.2006) 
(list 4800.135 868.2108) 
(list 4800.135 868.2211) 
(list 4800.135 868.2314) 
(list 4800.135 868.2417) 
(list 4800.135 868.2519) 
(list 4800.135 868.2622) 
(list 4800.135 868.2725) 
(list 4800.135 868.2828) 
(list 4800.135 868.2931) 
(list 4800.135 868.3033) 
(list 4800.135 868.3136) 
(list 4800.135 868.3239) 
(list 4800.135 868.3342) 
(list 4800.135 868.3444) 
(list 4800.135 868.3547) 
(list 4800.135 868.365) 
(list 4800.135 868.3753) 
(list 4800.135 868.3856) 
(list 4800.135 868.3958) 
(list 4800.135 868.4061) 
(list 4800.135 868.4164) 
(list 4800.135 868.4267) 
(list 4800.135 868.4369) 
(list 4800.135 868.4472) 
(list 4800.135 868.4575) 
(list 4800.135 868.4678) 
(list 4800.135 868.4781) 
(list 4800.135 868.4883) 
(list 4800.135 868.4986) 
(list 4800.135 868.5089) 
(list 4800.135 868.5192) 
(list 4800.135 868.5294) 
(list 4800.135 868.5397) 
(list 4800.135 868.55) 
(list 4800 868.55)))
(apply 'command (append '("pline") coords '("c")))
(setq tap15 (ssadd (entlast) tap15))
(command "_mirror" (entlast) "" "4800,900" "4800,901" "No")
(setq tap15 (ssadd (entlast) tap15))
(setq coords (list 
(list 4800.466 868.18) 
(list 4800.4558 868.18) 
(list 4800.4555 868.1903) 
(list 4800.4542 868.2006) 
(list 4800.4517 868.2108) 
(list 4800.4483 868.2211) 
(list 4800.4439 868.2314) 
(list 4800.4388 868.2417) 
(list 4800.4329 868.2519) 
(list 4800.4267 868.2622) 
(list 4800.4201 868.2725) 
(list 4800.4134 868.2828) 
(list 4800.4069 868.2931) 
(list 4800.4007 868.3033) 
(list 4800.395 868.3136) 
(list 4800.39 868.3239) 
(list 4800.3859 868.3342) 
(list 4800.3827 868.3444) 
(list 4800.3807 868.3547) 
(list 4800.3799 868.365) 
(list 4800.3803 868.3753) 
(list 4800.3819 868.3856) 
(list 4800.3848 868.3958) 
(list 4800.3887 868.4061) 
(list 4800.3937 868.4164) 
(list 4800.3996 868.4267) 
(list 4800.4062 868.4369) 
(list 4800.4133 868.4472) 
(list 4800.4207 868.4575) 
(list 4800.4282 868.4678) 
(list 4800.4356 868.4781) 
(list 4800.4425 868.4883) 
(list 4800.449 868.4986) 
(list 4800.4546 868.5089) 
(list 4800.4592 868.5192) 
(list 4800.4627 868.5294) 
(list 4800.465 868.5397) 
(list 4800.466 868.55) 
(list 4800.466 868.55)))
(apply 'command (append '("pline") coords '("c")))
(setq tap15 (ssadd (entlast) tap15))
(command "_mirror" (entlast) "" "4800,900" "4800,901" "No")
(setq tap15 (ssadd (entlast) tap15))
(setq coords (list 
(list 4801.136 868.18) 
(list 4800.466 868.18) 
(list 4800.466 868.1903) 
(list 4800.466 868.2006) 
(list 4800.466 868.2108) 
(list 4800.466 868.2211) 
(list 4800.466 868.2314) 
(list 4800.466 868.2417) 
(list 4800.466 868.2519) 
(list 4800.466 868.2622) 
(list 4800.466 868.2725) 
(list 4800.466 868.2828) 
(list 4800.466 868.2931) 
(list 4800.466 868.3033) 
(list 4800.466 868.3136) 
(list 4800.466 868.3239) 
(list 4800.466 868.3342) 
(list 4800.466 868.3444) 
(list 4800.466 868.3547) 
(list 4800.466 868.365) 
(list 4800.466 868.3753) 
(list 4800.466 868.3856) 
(list 4800.466 868.3958) 
(list 4800.466 868.4061) 
(list 4800.466 868.4164) 
(list 4800.466 868.4267) 
(list 4800.466 868.4369) 
(list 4800.466 868.4472) 
(list 4800.466 868.4575) 
(list 4800.466 868.4678) 
(list 4800.466 868.4781) 
(list 4800.466 868.4883) 
(list 4800.466 868.4986) 
(list 4800.466 868.5089) 
(list 4800.466 868.5192) 
(list 4800.466 868.5294) 
(list 4800.466 868.5397) 
(list 4800.466 868.55) 
(list 4801.136 868.55)))
(apply 'command (append '("pline") coords '("c")))
(setq tap15 (ssadd (entlast) tap15))
(command "_mirror" (entlast) "" "4800,900" "4800,901" "No")
(setq tap15 (ssadd (entlast) tap15))
(setq coords (list 
(list 4800 868.55) 
(list 4800.135 868.55) 
(list 4800.135 868.5603) 
(list 4800.135 868.5706) 
(list 4800.135 868.5808) 
(list 4800.135 868.5911) 
(list 4800.135 868.6014) 
(list 4800.135 868.6117) 
(list 4800.135 868.6219) 
(list 4800.135 868.6322) 
(list 4800.135 868.6425) 
(list 4800.135 868.6528) 
(list 4800.135 868.6631) 
(list 4800.135 868.6733) 
(list 4800.135 868.6836) 
(list 4800.135 868.6939) 
(list 4800.135 868.7042) 
(list 4800.135 868.7144) 
(list 4800.135 868.7247) 
(list 4800.135 868.735) 
(list 4800.135 868.7453) 
(list 4800.135 868.7556) 
(list 4800.135 868.7658) 
(list 4800.135 868.7761) 
(list 4800.135 868.7864) 
(list 4800.135 868.7967) 
(list 4800.135 868.8069) 
(list 4800.135 868.8172) 
(list 4800.135 868.8275) 
(list 4800.135 868.8378) 
(list 4800.135 868.8481) 
(list 4800.135 868.8583) 
(list 4800.135 868.8686) 
(list 4800.135 868.8789) 
(list 4800.135 868.8892) 
(list 4800.135 868.8994) 
(list 4800.135 868.9097) 
(list 4800.135 868.92) 
(list 4800 868.92)))
(apply 'command (append '("pline") coords '("c")))
(setq tap15 (ssadd (entlast) tap15))
(command "_mirror" (entlast) "" "4800,900" "4800,901" "No")
(setq tap15 (ssadd (entlast) tap15))
(setq coords (list 
(list 4800.4762 868.55) 
(list 4800.466 868.55) 
(list 4800.4656 868.5603) 
(list 4800.4638 868.5706) 
(list 4800.4607 868.5808) 
(list 4800.4564 868.5911) 
(list 4800.4509 868.6014) 
(list 4800.4444 868.6117) 
(list 4800.4372 868.6219) 
(list 4800.4294 868.6322) 
(list 4800.4213 868.6425) 
(list 4800.4131 868.6528) 
(list 4800.405 868.6631) 
(list 4800.3974 868.6733) 
(list 4800.3904 868.6836) 
(list 4800.3843 868.6939) 
(list 4800.3793 868.7042) 
(list 4800.3755 868.7144) 
(list 4800.3731 868.7247) 
(list 4800.3721 868.735) 
(list 4800.3726 868.7453) 
(list 4800.3747 868.7556) 
(list 4800.3782 868.7658) 
(list 4800.383 868.7761) 
(list 4800.3891 868.7864) 
(list 4800.3963 868.7967) 
(list 4800.4043 868.8069) 
(list 4800.4129 868.8172) 
(list 4800.4219 868.8275) 
(list 4800.431 868.8378) 
(list 4800.4398 868.8481) 
(list 4800.4483 868.8583) 
(list 4800.4559 868.8686) 
(list 4800.4627 868.8789) 
(list 4800.4682 868.8892) 
(list 4800.4724 868.8994) 
(list 4800.4751 868.9097) 
(list 4800.4762 868.92) 
(list 4800.4762 868.92)))
(apply 'command (append '("pline") coords '("c")))
(setq tap15 (ssadd (entlast) tap15))
(command "_mirror" (entlast) "" "4800,900" "4800,901" "No")
(setq tap15 (ssadd (entlast) tap15))
(setq coords (list 
(list 4801.136 868.55) 
(list 4800.4762 868.55) 
(list 4800.4762 868.5603) 
(list 4800.4762 868.5706) 
(list 4800.4762 868.5808) 
(list 4800.4762 868.5911) 
(list 4800.4762 868.6014) 
(list 4800.4762 868.6117) 
(list 4800.4762 868.6219) 
(list 4800.4762 868.6322) 
(list 4800.4762 868.6425) 
(list 4800.4762 868.6528) 
(list 4800.4762 868.6631) 
(list 4800.4762 868.6733) 
(list 4800.4762 868.6836) 
(list 4800.4762 868.6939) 
(list 4800.4762 868.7042) 
(list 4800.4762 868.7144) 
(list 4800.4762 868.7247) 
(list 4800.4762 868.735) 
(list 4800.4762 868.7453) 
(list 4800.4762 868.7556) 
(list 4800.4762 868.7658) 
(list 4800.4762 868.7761) 
(list 4800.4762 868.7864) 
(list 4800.4762 868.7967) 
(list 4800.4762 868.8069) 
(list 4800.4762 868.8172) 
(list 4800.4762 868.8275) 
(list 4800.4762 868.8378) 
(list 4800.4762 868.8481) 
(list 4800.4762 868.8583) 
(list 4800.4762 868.8686) 
(list 4800.4762 868.8789) 
(list 4800.4762 868.8892) 
(list 4800.4762 868.8994) 
(list 4800.4762 868.9097) 
(list 4800.4762 868.92) 
(list 4801.136 868.92)))
(apply 'command (append '("pline") coords '("c")))
(setq tap15 (ssadd (entlast) tap15))
(command "_mirror" (entlast) "" "4800,900" "4800,901" "No")
(setq tap15 (ssadd (entlast) tap15))
(setq coords (list 
(list 4800 868.92) 
(list 4800.135 868.92) 
(list 4800.135 868.9303) 
(list 4800.135 868.9406) 
(list 4800.135 868.9508) 
(list 4800.135 868.9611) 
(list 4800.135 868.9714) 
(list 4800.135 868.9817) 
(list 4800.135 868.9919) 
(list 4800.135 869.0022) 
(list 4800.135 869.0125) 
(list 4800.135 869.0228) 
(list 4800.135 869.0331) 
(list 4800.135 869.0433) 
(list 4800.135 869.0536) 
(list 4800.135 869.0639) 
(list 4800.135 869.0742) 
(list 4800.135 869.0844) 
(list 4800.135 869.0947) 
(list 4800.135 869.105) 
(list 4800.135 869.1153) 
(list 4800.135 869.1256) 
(list 4800.135 869.1358) 
(list 4800.135 869.1461) 
(list 4800.135 869.1564) 
(list 4800.135 869.1667) 
(list 4800.135 869.1769) 
(list 4800.135 869.1872) 
(list 4800.135 869.1975) 
(list 4800.135 869.2078) 
(list 4800.135 869.2181) 
(list 4800.135 869.2283) 
(list 4800.135 869.2386) 
(list 4800.135 869.2489) 
(list 4800.135 869.2592) 
(list 4800.135 869.2694) 
(list 4800.135 869.2797) 
(list 4800.135 869.29) 
(list 4800 869.29)))
(apply 'command (append '("pline") coords '("c")))
(setq tap15 (ssadd (entlast) tap15))
(command "_mirror" (entlast) "" "4800,900" "4800,901" "No")
(setq tap15 (ssadd (entlast) tap15))
(setq coords (list 
(list 4800.4864 868.92) 
(list 4800.4762 868.92) 
(list 4800.4757 868.9303) 
(list 4800.4735 868.9406) 
(list 4800.4697 868.9508) 
(list 4800.4645 868.9611) 
(list 4800.4579 868.9714) 
(list 4800.4501 868.9817) 
(list 4800.4415 868.9919) 
(list 4800.4322 869.0022) 
(list 4800.4225 869.0125) 
(list 4800.4127 869.0228) 
(list 4800.4032 869.0331) 
(list 4800.3941 869.0433) 
(list 4800.3858 869.0536) 
(list 4800.3786 869.0639) 
(list 4800.3727 869.0742) 
(list 4800.3682 869.0844) 
(list 4800.3654 869.0947) 
(list 4800.3643 869.105) 
(list 4800.365 869.1153) 
(list 4800.3674 869.1256) 
(list 4800.3716 869.1358) 
(list 4800.3774 869.1461) 
(list 4800.3846 869.1564) 
(list 4800.393 869.1667) 
(list 4800.4024 869.1769) 
(list 4800.4126 869.1872) 
(list 4800.4231 869.1975) 
(list 4800.4337 869.2078) 
(list 4800.4441 869.2181) 
(list 4800.454 869.2283) 
(list 4800.4629 869.2386) 
(list 4800.4708 869.2489) 
(list 4800.4772 869.2592) 
(list 4800.4821 869.2694) 
(list 4800.4852 869.2797) 
(list 4800.4864 869.29) 
(list 4800.4864 869.29)))
(apply 'command (append '("pline") coords '("c")))
(setq tap15 (ssadd (entlast) tap15))
(command "_mirror" (entlast) "" "4800,900" "4800,901" "No")
(setq tap15 (ssadd (entlast) tap15))
(setq coords (list 
(list 4801.136 868.92) 
(list 4800.4864 868.92) 
(list 4800.4864 868.9303) 
(list 4800.4864 868.9406) 
(list 4800.4864 868.9508) 
(list 4800.4864 868.9611) 
(list 4800.4864 868.9714) 
(list 4800.4864 868.9817) 
(list 4800.4864 868.9919) 
(list 4800.4864 869.0022) 
(list 4800.4864 869.0125) 
(list 4800.4864 869.0228) 
(list 4800.4864 869.0331) 
(list 4800.4864 869.0433) 
(list 4800.4864 869.0536) 
(list 4800.4864 869.0639) 
(list 4800.4864 869.0742) 
(list 4800.4864 869.0844) 
(list 4800.4864 869.0947) 
(list 4800.4864 869.105) 
(list 4800.4864 869.1153) 
(list 4800.4864 869.1256) 
(list 4800.4864 869.1358) 
(list 4800.4864 869.1461) 
(list 4800.4864 869.1564) 
(list 4800.4864 869.1667) 
(list 4800.4864 869.1769) 
(list 4800.4864 869.1872) 
(list 4800.4864 869.1975) 
(list 4800.4864 869.2078) 
(list 4800.4864 869.2181) 
(list 4800.4864 869.2283) 
(list 4800.4864 869.2386) 
(list 4800.4864 869.2489) 
(list 4800.4864 869.2592) 
(list 4800.4864 869.2694) 
(list 4800.4864 869.2797) 
(list 4800.4864 869.29) 
(list 4801.136 869.29)))
(apply 'command (append '("pline") coords '("c")))
(setq tap15 (ssadd (entlast) tap15))
(command "_mirror" (entlast) "" "4800,900" "4800,901" "No")
(setq tap15 (ssadd (entlast) tap15))
(setq coords (list 
(list 4800 869.29) 
(list 4800.135 869.29) 
(list 4800.135 869.3003) 
(list 4800.135 869.3106) 
(list 4800.135 869.3208) 
(list 4800.135 869.3311) 
(list 4800.135 869.3414) 
(list 4800.135 869.3517) 
(list 4800.135 869.3619) 
(list 4800.135 869.3722) 
(list 4800.135 869.3825) 
(list 4800.135 869.3928) 
(list 4800.135 869.4031) 
(list 4800.135 869.4133) 
(list 4800.135 869.4236) 
(list 4800.135 869.4339) 
(list 4800.135 869.4442) 
(list 4800.135 869.4544) 
(list 4800.135 869.4647) 
(list 4800.135 869.475) 
(list 4800.135 869.4853) 
(list 4800.135 869.4956) 
(list 4800.135 869.5058) 
(list 4800.135 869.5161) 
(list 4800.135 869.5264) 
(list 4800.135 869.5367) 
(list 4800.135 869.5469) 
(list 4800.135 869.5572) 
(list 4800.135 869.5675) 
(list 4800.135 869.5778) 
(list 4800.135 869.5881) 
(list 4800.135 869.5983) 
(list 4800.135 869.6086) 
(list 4800.135 869.6189) 
(list 4800.135 869.6292) 
(list 4800.135 869.6394) 
(list 4800.135 869.6497) 
(list 4800.135 869.66) 
(list 4800 869.66)))
(apply 'command (append '("pline") coords '("c")))
(setq tap15 (ssadd (entlast) tap15))
(command "_mirror" (entlast) "" "4800,900" "4800,901" "No")
(setq tap15 (ssadd (entlast) tap15))
(setq coords (list 
(list 4800.4966 869.29) 
(list 4800.4864 869.29) 
(list 4800.4857 869.3003) 
(list 4800.4831 869.3106) 
(list 4800.4787 869.3208) 
(list 4800.4726 869.3311) 
(list 4800.4649 869.3414) 
(list 4800.4559 869.3517) 
(list 4800.4458 869.3619) 
(list 4800.435 869.3722) 
(list 4800.4237 869.3825) 
(list 4800.4124 869.3928) 
(list 4800.4013 869.4031) 
(list 4800.3908 869.4133) 
(list 4800.3812 869.4236) 
(list 4800.3729 869.4339) 
(list 4800.3661 869.4442) 
(list 4800.361 869.4544) 
(list 4800.3577 869.4647) 
(list 4800.3565 869.475) 
(list 4800.3573 869.4853) 
(list 4800.3602 869.4956) 
(list 4800.365 869.5058) 
(list 4800.3717 869.5161) 
(list 4800.38 869.5264) 
(list 4800.3897 869.5367) 
(list 4800.4005 869.5469) 
(list 4800.4122 869.5572) 
(list 4800.4243 869.5675) 
(list 4800.4365 869.5778) 
(list 4800.4484 869.5881) 
(list 4800.4596 869.5983) 
(list 4800.4699 869.6086) 
(list 4800.4789 869.6189) 
(list 4800.4862 869.6292) 
(list 4800.4917 869.6394) 
(list 4800.4952 869.6497) 
(list 4800.4966 869.66) 
(list 4800.4966 869.66)))
(apply 'command (append '("pline") coords '("c")))
(setq tap15 (ssadd (entlast) tap15))
(command "_mirror" (entlast) "" "4800,900" "4800,901" "No")
(setq tap15 (ssadd (entlast) tap15))
(setq coords (list 
(list 4801.136 869.29) 
(list 4800.4966 869.29) 
(list 4800.4966 869.3003) 
(list 4800.4966 869.3106) 
(list 4800.4966 869.3208) 
(list 4800.4966 869.3311) 
(list 4800.4966 869.3414) 
(list 4800.4966 869.3517) 
(list 4800.4966 869.3619) 
(list 4800.4966 869.3722) 
(list 4800.4966 869.3825) 
(list 4800.4966 869.3928) 
(list 4800.4966 869.4031) 
(list 4800.4966 869.4133) 
(list 4800.4966 869.4236) 
(list 4800.4966 869.4339) 
(list 4800.4966 869.4442) 
(list 4800.4966 869.4544) 
(list 4800.4966 869.4647) 
(list 4800.4966 869.475) 
(list 4800.4966 869.4853) 
(list 4800.4966 869.4956) 
(list 4800.4966 869.5058) 
(list 4800.4966 869.5161) 
(list 4800.4966 869.5264) 
(list 4800.4966 869.5367) 
(list 4800.4966 869.5469) 
(list 4800.4966 869.5572) 
(list 4800.4966 869.5675) 
(list 4800.4966 869.5778) 
(list 4800.4966 869.5881) 
(list 4800.4966 869.5983) 
(list 4800.4966 869.6086) 
(list 4800.4966 869.6189) 
(list 4800.4966 869.6292) 
(list 4800.4966 869.6394) 
(list 4800.4966 869.6497) 
(list 4800.4966 869.66) 
(list 4801.136 869.66)))
(apply 'command (append '("pline") coords '("c")))
(setq tap15 (ssadd (entlast) tap15))
(command "_mirror" (entlast) "" "4800,900" "4800,901" "No")
(setq tap15 (ssadd (entlast) tap15))
(setq coords (list 
(list 4800 869.66) 
(list 4800.135 869.66) 
(list 4800.135 869.6703) 
(list 4800.135 869.6806) 
(list 4800.135 869.6908) 
(list 4800.135 869.7011) 
(list 4800.135 869.7114) 
(list 4800.135 869.7217) 
(list 4800.135 869.7319) 
(list 4800.135 869.7422) 
(list 4800.135 869.7525) 
(list 4800.135 869.7628) 
(list 4800.135 869.7731) 
(list 4800.135 869.7833) 
(list 4800.135 869.7936) 
(list 4800.135 869.8039) 
(list 4800.135 869.8142) 
(list 4800.135 869.8244) 
(list 4800.135 869.8347) 
(list 4800.135 869.845) 
(list 4800.135 869.8553) 
(list 4800.135 869.8656) 
(list 4800.135 869.8758) 
(list 4800.135 869.8861) 
(list 4800.135 869.8964) 
(list 4800.135 869.9067) 
(list 4800.135 869.9169) 
(list 4800.135 869.9272) 
(list 4800.135 869.9375) 
(list 4800.135 869.9478) 
(list 4800.135 869.9581) 
(list 4800.135 869.9683) 
(list 4800.135 869.9786) 
(list 4800.135 869.9889) 
(list 4800.135 869.9992) 
(list 4800.135 870.0094) 
(list 4800.135 870.0197) 
(list 4800.135 870.03) 
(list 4800 870.03)))
(apply 'command (append '("pline") coords '("c")))
(setq tap15 (ssadd (entlast) tap15))
(command "_mirror" (entlast) "" "4800,900" "4800,901" "No")
(setq tap15 (ssadd (entlast) tap15))
(setq coords (list 
(list 4800.5068 869.66) 
(list 4800.4966 869.66) 
(list 4800.4958 869.6703) 
(list 4800.4928 869.6806) 
(list 4800.4877 869.6908) 
(list 4800.4807 869.7011) 
(list 4800.4719 869.7114) 
(list 4800.4615 869.7217) 
(list 4800.4501 869.7319) 
(list 4800.4377 869.7422) 
(list 4800.4249 869.7525) 
(list 4800.412 869.7628) 
(list 4800.3994 869.7731) 
(list 4800.3875 869.7833) 
(list 4800.3767 869.7936) 
(list 4800.3672 869.8039) 
(list 4800.3595 869.8142) 
(list 4800.3537 869.8244) 
(list 4800.3501 869.8347) 
(list 4800.3487 869.845) 
(list 4800.3496 869.8553) 
(list 4800.3529 869.8656) 
(list 4800.3584 869.8758) 
(list 4800.366 869.8861) 
(list 4800.3754 869.8964) 
(list 4800.3864 869.9067) 
(list 4800.3987 869.9169) 
(list 4800.4118 869.9272) 
(list 4800.4255 869.9375) 
(list 4800.4393 869.9478) 
(list 4800.4527 869.9581) 
(list 4800.4654 869.9683) 
(list 4800.4769 869.9786) 
(list 4800.487 869.9889) 
(list 4800.4952 869.9992) 
(list 4800.5014 870.0094) 
(list 4800.5053 870.0197) 
(list 4800.5068 870.03) 
(list 4800.5068 870.03)))
(apply 'command (append '("pline") coords '("c")))
(setq tap15 (ssadd (entlast) tap15))
(command "_mirror" (entlast) "" "4800,900" "4800,901" "No")
(setq tap15 (ssadd (entlast) tap15))
(setq coords (list 
(list 4801.136 869.66) 
(list 4800.5068 869.66) 
(list 4800.5068 869.6703) 
(list 4800.5068 869.6806) 
(list 4800.5068 869.6908) 
(list 4800.5068 869.7011) 
(list 4800.5068 869.7114) 
(list 4800.5068 869.7217) 
(list 4800.5068 869.7319) 
(list 4800.5068 869.7422) 
(list 4800.5068 869.7525) 
(list 4800.5068 869.7628) 
(list 4800.5068 869.7731) 
(list 4800.5068 869.7833) 
(list 4800.5068 869.7936) 
(list 4800.5068 869.8039) 
(list 4800.5068 869.8142) 
(list 4800.5068 869.8244) 
(list 4800.5068 869.8347) 
(list 4800.5068 869.845) 
(list 4800.5068 869.8553) 
(list 4800.5068 869.8656) 
(list 4800.5068 869.8758) 
(list 4800.5068 869.8861) 
(list 4800.5068 869.8964) 
(list 4800.5068 869.9067) 
(list 4800.5068 869.9169) 
(list 4800.5068 869.9272) 
(list 4800.5068 869.9375) 
(list 4800.5068 869.9478) 
(list 4800.5068 869.9581) 
(list 4800.5068 869.9683) 
(list 4800.5068 869.9786) 
(list 4800.5068 869.9889) 
(list 4800.5068 869.9992) 
(list 4800.5068 870.0094) 
(list 4800.5068 870.0197) 
(list 4800.5068 870.03) 
(list 4801.136 870.03)))
(apply 'command (append '("pline") coords '("c")))
(setq tap15 (ssadd (entlast) tap15))
(command "_mirror" (entlast) "" "4800,900" "4800,901" "No")
(setq tap15 (ssadd (entlast) tap15))
(setq coords (list 
(list 4800 870.03) 
(list 4800.135 870.03) 
(list 4800.135 870.0403) 
(list 4800.135 870.0506) 
(list 4800.135 870.0608) 
(list 4800.135 870.0711) 
(list 4800.135 870.0814) 
(list 4800.135 870.0917) 
(list 4800.135 870.1019) 
(list 4800.135 870.1122) 
(list 4800.135 870.1225) 
(list 4800.135 870.1328) 
(list 4800.135 870.1431) 
(list 4800.135 870.1533) 
(list 4800.135 870.1636) 
(list 4800.135 870.1739) 
(list 4800.135 870.1842) 
(list 4800.135 870.1944) 
(list 4800.135 870.2047) 
(list 4800.135 870.215) 
(list 4800.135 870.2253) 
(list 4800.135 870.2356) 
(list 4800.135 870.2458) 
(list 4800.135 870.2561) 
(list 4800.135 870.2664) 
(list 4800.135 870.2767) 
(list 4800.135 870.2869) 
(list 4800.135 870.2972) 
(list 4800.135 870.3075) 
(list 4800.135 870.3178) 
(list 4800.135 870.3281) 
(list 4800.135 870.3383) 
(list 4800.135 870.3486) 
(list 4800.135 870.3589) 
(list 4800.135 870.3692) 
(list 4800.135 870.3794) 
(list 4800.135 870.3897) 
(list 4800.135 870.4) 
(list 4800 870.4)))
(apply 'command (append '("pline") coords '("c")))
(setq tap15 (ssadd (entlast) tap15))
(command "_mirror" (entlast) "" "4800,900" "4800,901" "No")
(setq tap15 (ssadd (entlast) tap15))
(setq coords (list 
(list 4800.517 870.03) 
(list 4800.5068 870.03) 
(list 4800.5058 870.0403) 
(list 4800.5025 870.0506) 
(list 4800.4967 870.0608) 
(list 4800.4887 870.0711) 
(list 4800.4788 870.0814) 
(list 4800.4672 870.0917) 
(list 4800.4543 870.1019) 
(list 4800.4405 870.1122) 
(list 4800.4261 870.1225) 
(list 4800.4116 870.1328) 
(list 4800.3975 870.1431) 
(list 4800.3842 870.1533) 
(list 4800.3721 870.1636) 
(list 4800.3615 870.1739) 
(list 4800.3529 870.1842) 
(list 4800.3465 870.1944) 
(list 4800.3424 870.2047) 
(list 4800.3409 870.215) 
(list 4800.342 870.2253) 
(list 4800.3457 870.2356) 
(list 4800.3518 870.2458) 
(list 4800.3603 870.2561) 
(list 4800.3708 870.2664) 
(list 4800.3831 870.2767) 
(list 4800.3968 870.2869) 
(list 4800.4115 870.2972) 
(list 4800.4267 870.3075) 
(list 4800.442 870.3178) 
(list 4800.4569 870.3281) 
(list 4800.4711 870.3383) 
(list 4800.4839 870.3486) 
(list 4800.495 870.3589) 
(list 4800.5042 870.3692) 
(list 4800.511 870.3794) 
(list 4800.5154 870.3897) 
(list 4800.517 870.4) 
(list 4800.517 870.4)))
(apply 'command (append '("pline") coords '("c")))
(setq tap15 (ssadd (entlast) tap15))
(command "_mirror" (entlast) "" "4800,900" "4800,901" "No")
(setq tap15 (ssadd (entlast) tap15))
(setq coords (list 
(list 4801.136 870.03) 
(list 4800.517 870.03) 
(list 4800.517 870.0403) 
(list 4800.517 870.0506) 
(list 4800.517 870.0608) 
(list 4800.517 870.0711) 
(list 4800.517 870.0814) 
(list 4800.517 870.0917) 
(list 4800.517 870.1019) 
(list 4800.517 870.1122) 
(list 4800.517 870.1225) 
(list 4800.517 870.1328) 
(list 4800.517 870.1431) 
(list 4800.517 870.1533) 
(list 4800.517 870.1636) 
(list 4800.517 870.1739) 
(list 4800.517 870.1842) 
(list 4800.517 870.1944) 
(list 4800.517 870.2047) 
(list 4800.517 870.215) 
(list 4800.517 870.2253) 
(list 4800.517 870.2356) 
(list 4800.517 870.2458) 
(list 4800.517 870.2561) 
(list 4800.517 870.2664) 
(list 4800.517 870.2767) 
(list 4800.517 870.2869) 
(list 4800.517 870.2972) 
(list 4800.517 870.3075) 
(list 4800.517 870.3178) 
(list 4800.517 870.3281) 
(list 4800.517 870.3383) 
(list 4800.517 870.3486) 
(list 4800.517 870.3589) 
(list 4800.517 870.3692) 
(list 4800.517 870.3794) 
(list 4800.517 870.3897) 
(list 4800.517 870.4) 
(list 4801.136 870.4)))
(apply 'command (append '("pline") coords '("c")))
(setq tap15 (ssadd (entlast) tap15))
(command "_mirror" (entlast) "" "4800,900" "4800,901" "No")
(setq tap15 (ssadd (entlast) tap15))
(setq coords (list 
(list 4800 870.4) 
(list 4800.135 870.4) 
(list 4800.135 870.4103) 
(list 4800.135 870.4206) 
(list 4800.135 870.4308) 
(list 4800.135 870.4411) 
(list 4800.135 870.4514) 
(list 4800.135 870.4617) 
(list 4800.135 870.4719) 
(list 4800.135 870.4822) 
(list 4800.135 870.4925) 
(list 4800.135 870.5028) 
(list 4800.135 870.5131) 
(list 4800.135 870.5233) 
(list 4800.135 870.5336) 
(list 4800.135 870.5439) 
(list 4800.135 870.5542) 
(list 4800.135 870.5644) 
(list 4800.135 870.5747) 
(list 4800.135 870.585) 
(list 4800.135 870.5953) 
(list 4800.135 870.6056) 
(list 4800.135 870.6158) 
(list 4800.135 870.6261) 
(list 4800.135 870.6364) 
(list 4800.135 870.6467) 
(list 4800.135 870.6569) 
(list 4800.135 870.6672) 
(list 4800.135 870.6775) 
(list 4800.135 870.6878) 
(list 4800.135 870.6981) 
(list 4800.135 870.7083) 
(list 4800.135 870.7186) 
(list 4800.135 870.7289) 
(list 4800.135 870.7392) 
(list 4800.135 870.7494) 
(list 4800.135 870.7597) 
(list 4800.135 870.77) 
(list 4800 870.77)))
(apply 'command (append '("pline") coords '("c")))
(setq tap15 (ssadd (entlast) tap15))
(command "_mirror" (entlast) "" "4800,900" "4800,901" "No")
(setq tap15 (ssadd (entlast) tap15))
(setq coords (list 
(list 4800.5272 870.4) 
(list 4800.517 870.4) 
(list 4800.5159 870.4103) 
(list 4800.5121 870.4206) 
(list 4800.5057 870.4308) 
(list 4800.4968 870.4411) 
(list 4800.4858 870.4514) 
(list 4800.473 870.4617) 
(list 4800.4586 870.4719) 
(list 4800.4432 870.4822) 
(list 4800.4273 870.4925) 
(list 4800.4113 870.5028) 
(list 4800.3956 870.5131) 
(list 4800.3809 870.5233) 
(list 4800.3675 870.5336) 
(list 4800.3558 870.5439) 
(list 4800.3463 870.5542) 
(list 4800.3392 870.5644) 
(list 4800.3347 870.5747) 
(list 4800.3331 870.585) 
(list 4800.3343 870.5953) 
(list 4800.3384 870.6056) 
(list 4800.3452 870.6158) 
(list 4800.3546 870.6261) 
(list 4800.3662 870.6364) 
(list 4800.3798 870.6467) 
(list 4800.3949 870.6569) 
(list 4800.4111 870.6672) 
(list 4800.4279 870.6775) 
(list 4800.4448 870.6878) 
(list 4800.4612 870.6981) 
(list 4800.4767 870.7083) 
(list 4800.4909 870.7186) 
(list 4800.5031 870.7289) 
(list 4800.5132 870.7392) 
(list 4800.5207 870.7494) 
(list 4800.5254 870.7597) 
(list 4800.5272 870.77) 
(list 4800.5272 870.77)))
(apply 'command (append '("pline") coords '("c")))
(setq tap15 (ssadd (entlast) tap15))
(command "_mirror" (entlast) "" "4800,900" "4800,901" "No")
(setq tap15 (ssadd (entlast) tap15))
(setq coords (list 
(list 4801.136 870.4) 
(list 4800.5272 870.4) 
(list 4800.5272 870.4103) 
(list 4800.5272 870.4206) 
(list 4800.5272 870.4308) 
(list 4800.5272 870.4411) 
(list 4800.5272 870.4514) 
(list 4800.5272 870.4617) 
(list 4800.5272 870.4719) 
(list 4800.5272 870.4822) 
(list 4800.5272 870.4925) 
(list 4800.5272 870.5028) 
(list 4800.5272 870.5131) 
(list 4800.5272 870.5233) 
(list 4800.5272 870.5336) 
(list 4800.5272 870.5439) 
(list 4800.5272 870.5542) 
(list 4800.5272 870.5644) 
(list 4800.5272 870.5747) 
(list 4800.5272 870.585) 
(list 4800.5272 870.5953) 
(list 4800.5272 870.6056) 
(list 4800.5272 870.6158) 
(list 4800.5272 870.6261) 
(list 4800.5272 870.6364) 
(list 4800.5272 870.6467) 
(list 4800.5272 870.6569) 
(list 4800.5272 870.6672) 
(list 4800.5272 870.6775) 
(list 4800.5272 870.6878) 
(list 4800.5272 870.6981) 
(list 4800.5272 870.7083) 
(list 4800.5272 870.7186) 
(list 4800.5272 870.7289) 
(list 4800.5272 870.7392) 
(list 4800.5272 870.7494) 
(list 4800.5272 870.7597) 
(list 4800.5272 870.77) 
(list 4801.136 870.77)))
(apply 'command (append '("pline") coords '("c")))
(setq tap15 (ssadd (entlast) tap15))
(command "_mirror" (entlast) "" "4800,900" "4800,901" "No")
(setq tap15 (ssadd (entlast) tap15))
(setq coords (list 
(list 4800 870.77) 
(list 4800.135 870.77) 
(list 4800.135 870.7803) 
(list 4800.135 870.7906) 
(list 4800.135 870.8008) 
(list 4800.135 870.8111) 
(list 4800.135 870.8214) 
(list 4800.135 870.8317) 
(list 4800.135 870.8419) 
(list 4800.135 870.8522) 
(list 4800.135 870.8625) 
(list 4800.135 870.8728) 
(list 4800.135 870.8831) 
(list 4800.135 870.8933) 
(list 4800.135 870.9036) 
(list 4800.135 870.9139) 
(list 4800.135 870.9242) 
(list 4800.135 870.9344) 
(list 4800.135 870.9447) 
(list 4800.135 870.955) 
(list 4800.135 870.9653) 
(list 4800.135 870.9756) 
(list 4800.135 870.9858) 
(list 4800.135 870.9961) 
(list 4800.135 871.0064) 
(list 4800.135 871.0167) 
(list 4800.135 871.0269) 
(list 4800.135 871.0372) 
(list 4800.135 871.0475) 
(list 4800.135 871.0578) 
(list 4800.135 871.0681) 
(list 4800.135 871.0783) 
(list 4800.135 871.0886) 
(list 4800.135 871.0989) 
(list 4800.135 871.1092) 
(list 4800.135 871.1194) 
(list 4800.135 871.1297) 
(list 4800.135 871.14) 
(list 4800 871.14)))
(apply 'command (append '("pline") coords '("c")))
(setq tap15 (ssadd (entlast) tap15))
(command "_mirror" (entlast) "" "4800,900" "4800,901" "No")
(setq tap15 (ssadd (entlast) tap15))
(setq coords (list 
(list 4800.5374 870.77) 
(list 4800.5272 870.77) 
(list 4800.526 870.7803) 
(list 4800.5218 870.7906) 
(list 4800.5147 870.8008) 
(list 4800.5049 870.8111) 
(list 4800.4928 870.8214) 
(list 4800.4787 870.8317) 
(list 4800.4629 870.8419) 
(list 4800.446 870.8522) 
(list 4800.4285 870.8625) 
(list 4800.4109 870.8728) 
(list 4800.3938 870.8831) 
(list 4800.3776 870.8933) 
(list 4800.3629 870.9036) 
(list 4800.3501 870.9139) 
(list 4800.3397 870.9242) 
(list 4800.3319 870.9344) 
(list 4800.3271 870.9447) 
(list 4800.3253 870.955) 
(list 4800.3267 870.9653) 
(list 4800.3311 870.9756) 
(list 4800.3386 870.9858) 
(list 4800.3489 870.9961) 
(list 4800.3616 871.0064) 
(list 4800.3765 871.0167) 
(list 4800.393 871.0269) 
(list 4800.4107 871.0372) 
(list 4800.4291 871.0475) 
(list 4800.4475 871.0578) 
(list 4800.4655 871.0681) 
(list 4800.4825 871.0783) 
(list 4800.4979 871.0886) 
(list 4800.5112 871.0989) 
(list 4800.5222 871.1092) 
(list 4800.5303 871.1194) 
(list 4800.5355 871.1297) 
(list 4800.5374 871.14) 
(list 4800.5374 871.14)))
(apply 'command (append '("pline") coords '("c")))
(setq tap15 (ssadd (entlast) tap15))
(command "_mirror" (entlast) "" "4800,900" "4800,901" "No")
(setq tap15 (ssadd (entlast) tap15))
(setq coords (list 
(list 4801.136 870.77) 
(list 4800.5374 870.77) 
(list 4800.5374 870.7803) 
(list 4800.5374 870.7906) 
(list 4800.5374 870.8008) 
(list 4800.5374 870.8111) 
(list 4800.5374 870.8214) 
(list 4800.5374 870.8317) 
(list 4800.5374 870.8419) 
(list 4800.5374 870.8522) 
(list 4800.5374 870.8625) 
(list 4800.5374 870.8728) 
(list 4800.5374 870.8831) 
(list 4800.5374 870.8933) 
(list 4800.5374 870.9036) 
(list 4800.5374 870.9139) 
(list 4800.5374 870.9242) 
(list 4800.5374 870.9344) 
(list 4800.5374 870.9447) 
(list 4800.5374 870.955) 
(list 4800.5374 870.9653) 
(list 4800.5374 870.9756) 
(list 4800.5374 870.9858) 
(list 4800.5374 870.9961) 
(list 4800.5374 871.0064) 
(list 4800.5374 871.0167) 
(list 4800.5374 871.0269) 
(list 4800.5374 871.0372) 
(list 4800.5374 871.0475) 
(list 4800.5374 871.0578) 
(list 4800.5374 871.0681) 
(list 4800.5374 871.0783) 
(list 4800.5374 871.0886) 
(list 4800.5374 871.0989) 
(list 4800.5374 871.1092) 
(list 4800.5374 871.1194) 
(list 4800.5374 871.1297) 
(list 4800.5374 871.14) 
(list 4801.136 871.14)))
(apply 'command (append '("pline") coords '("c")))
(setq tap15 (ssadd (entlast) tap15))
(command "_mirror" (entlast) "" "4800,900" "4800,901" "No")
(setq tap15 (ssadd (entlast) tap15))
(setq coords (list 
(list 4800 871.14) 
(list 4800.135 871.14) 
(list 4800.135 871.1503) 
(list 4800.135 871.1606) 
(list 4800.135 871.1708) 
(list 4800.135 871.1811) 
(list 4800.135 871.1914) 
(list 4800.135 871.2017) 
(list 4800.135 871.2119) 
(list 4800.135 871.2222) 
(list 4800.135 871.2325) 
(list 4800.135 871.2428) 
(list 4800.135 871.2531) 
(list 4800.135 871.2633) 
(list 4800.135 871.2736) 
(list 4800.135 871.2839) 
(list 4800.135 871.2942) 
(list 4800.135 871.3044) 
(list 4800.135 871.3147) 
(list 4800.135 871.325) 
(list 4800.135 871.3353) 
(list 4800.135 871.3456) 
(list 4800.135 871.3558) 
(list 4800.135 871.3661) 
(list 4800.135 871.3764) 
(list 4800.135 871.3867) 
(list 4800.135 871.3969) 
(list 4800.135 871.4072) 
(list 4800.135 871.4175) 
(list 4800.135 871.4278) 
(list 4800.135 871.4381) 
(list 4800.135 871.4483) 
(list 4800.135 871.4586) 
(list 4800.135 871.4689) 
(list 4800.135 871.4792) 
(list 4800.135 871.4894) 
(list 4800.135 871.4997) 
(list 4800.135 871.51) 
(list 4800 871.51)))
(apply 'command (append '("pline") coords '("c")))
(setq tap15 (ssadd (entlast) tap15))
(command "_mirror" (entlast) "" "4800,900" "4800,901" "No")
(setq tap15 (ssadd (entlast) tap15))
(setq coords (list 
(list 4800.5476 871.14) 
(list 4800.5374 871.14) 
(list 4800.536 871.1503) 
(list 4800.5314 871.1606) 
(list 4800.5237 871.1708) 
(list 4800.513 871.1811) 
(list 4800.4998 871.1914) 
(list 4800.4843 871.2017) 
(list 4800.4672 871.2119) 
(list 4800.4488 871.2222) 
(list 4800.4297 871.2325) 
(list 4800.4105 871.2428) 
(list 4800.3919 871.2531) 
(list 4800.3743 871.2633) 
(list 4800.3583 871.2736) 
(list 4800.3445 871.2839) 
(list 4800.3331 871.2942) 
(list 4800.3247 871.3044) 
(list 4800.3194 871.3147) 
(list 4800.3175 871.325) 
(list 4800.319 871.3353) 
(list 4800.3239 871.3456) 
(list 4800.332 871.3558) 
(list 4800.3432 871.3661) 
(list 4800.357 871.3764) 
(list 4800.3732 871.3867) 
(list 4800.3912 871.3969) 
(list 4800.4104 871.4072) 
(list 4800.4303 871.4175) 
(list 4800.4503 871.4278) 
(list 4800.4698 871.4381) 
(list 4800.4882 871.4483) 
(list 4800.5048 871.4586) 
(list 4800.5193 871.4689) 
(list 4800.5312 871.4792) 
(list 4800.54 871.4894) 
(list 4800.5455 871.4997) 
(list 4800.5476 871.51) 
(list 4800.5476 871.51)))
(apply 'command (append '("pline") coords '("c")))
(setq tap15 (ssadd (entlast) tap15))
(command "_mirror" (entlast) "" "4800,900" "4800,901" "No")
(setq tap15 (ssadd (entlast) tap15))
(setq coords (list 
(list 4801.136 871.14) 
(list 4800.5476 871.14) 
(list 4800.5476 871.1503) 
(list 4800.5476 871.1606) 
(list 4800.5476 871.1708) 
(list 4800.5476 871.1811) 
(list 4800.5476 871.1914) 
(list 4800.5476 871.2017) 
(list 4800.5476 871.2119) 
(list 4800.5476 871.2222) 
(list 4800.5476 871.2325) 
(list 4800.5476 871.2428) 
(list 4800.5476 871.2531) 
(list 4800.5476 871.2633) 
(list 4800.5476 871.2736) 
(list 4800.5476 871.2839) 
(list 4800.5476 871.2942) 
(list 4800.5476 871.3044) 
(list 4800.5476 871.3147) 
(list 4800.5476 871.325) 
(list 4800.5476 871.3353) 
(list 4800.5476 871.3456) 
(list 4800.5476 871.3558) 
(list 4800.5476 871.3661) 
(list 4800.5476 871.3764) 
(list 4800.5476 871.3867) 
(list 4800.5476 871.3969) 
(list 4800.5476 871.4072) 
(list 4800.5476 871.4175) 
(list 4800.5476 871.4278) 
(list 4800.5476 871.4381) 
(list 4800.5476 871.4483) 
(list 4800.5476 871.4586) 
(list 4800.5476 871.4689) 
(list 4800.5476 871.4792) 
(list 4800.5476 871.4894) 
(list 4800.5476 871.4997) 
(list 4800.5476 871.51) 
(list 4801.136 871.51)))
(apply 'command (append '("pline") coords '("c")))
(setq tap15 (ssadd (entlast) tap15))
(command "_mirror" (entlast) "" "4800,900" "4800,901" "No")
(setq tap15 (ssadd (entlast) tap15))
(setq coords (list 
(list 4800 871.51) 
(list 4800.135 871.51) 
(list 4800.135 871.5203) 
(list 4800.135 871.5306) 
(list 4800.135 871.5408) 
(list 4800.135 871.5511) 
(list 4800.135 871.5614) 
(list 4800.135 871.5717) 
(list 4800.135 871.5819) 
(list 4800.135 871.5922) 
(list 4800.135 871.6025) 
(list 4800.135 871.6128) 
(list 4800.135 871.6231) 
(list 4800.135 871.6333) 
(list 4800.135 871.6436) 
(list 4800.135 871.6539) 
(list 4800.135 871.6642) 
(list 4800.135 871.6744) 
(list 4800.135 871.6847) 
(list 4800.135 871.695) 
(list 4800.135 871.7053) 
(list 4800.135 871.7156) 
(list 4800.135 871.7258) 
(list 4800.135 871.7361) 
(list 4800.135 871.7464) 
(list 4800.135 871.7567) 
(list 4800.135 871.7669) 
(list 4800.135 871.7772) 
(list 4800.135 871.7875) 
(list 4800.135 871.7978) 
(list 4800.135 871.8081) 
(list 4800.135 871.8183) 
(list 4800.135 871.8286) 
(list 4800.135 871.8389) 
(list 4800.135 871.8492) 
(list 4800.135 871.8594) 
(list 4800.135 871.8697) 
(list 4800.135 871.88) 
(list 4800 871.88)))
(apply 'command (append '("pline") coords '("c")))
(setq tap15 (ssadd (entlast) tap15))
(command "_mirror" (entlast) "" "4800,900" "4800,901" "No")
(setq tap15 (ssadd (entlast) tap15))
(setq coords (list 
(list 4800.5578 871.51) 
(list 4800.5476 871.51) 
(list 4800.5461 871.5203) 
(list 4800.5411 871.5306) 
(list 4800.5327 871.5408) 
(list 4800.5211 871.5511) 
(list 4800.5068 871.5614) 
(list 4800.4901 871.5717) 
(list 4800.4714 871.5819) 
(list 4800.4515 871.5922) 
(list 4800.4309 871.6025) 
(list 4800.4102 871.6128) 
(list 4800.39 871.6231) 
(list 4800.371 871.6333) 
(list 4800.3537 871.6436) 
(list 4800.3388 871.6539) 
(list 4800.3265 871.6642) 
(list 4800.3174 871.6744) 
(list 4800.3118 871.6847) 
(list 4800.3097 871.695) 
(list 4800.3113 871.7053) 
(list 4800.3166 871.7156) 
(list 4800.3254 871.7258) 
(list 4800.3375 871.7361) 
(list 4800.3525 871.7464) 
(list 4800.3699 871.7567) 
(list 4800.3893 871.7669) 
(list 4800.41 871.7772) 
(list 4800.4315 871.7875) 
(list 4800.4531 871.7978) 
(list 4800.4741 871.8081) 
(list 4800.4938 871.8183) 
(list 4800.5118 871.8286) 
(list 4800.5274 871.8389) 
(list 4800.5402 871.8492) 
(list 4800.5497 871.8594) 
(list 4800.5556 871.8697) 
(list 4800.5578 871.88) 
(list 4800.5578 871.88)))
(apply 'command (append '("pline") coords '("c")))
(setq tap15 (ssadd (entlast) tap15))
(command "_mirror" (entlast) "" "4800,900" "4800,901" "No")
(setq tap15 (ssadd (entlast) tap15))
(setq coords (list 
(list 4801.136 871.51) 
(list 4800.5578 871.51) 
(list 4800.5578 871.5203) 
(list 4800.5578 871.5306) 
(list 4800.5578 871.5408) 
(list 4800.5578 871.5511) 
(list 4800.5578 871.5614) 
(list 4800.5578 871.5717) 
(list 4800.5578 871.5819) 
(list 4800.5578 871.5922) 
(list 4800.5578 871.6025) 
(list 4800.5578 871.6128) 
(list 4800.5578 871.6231) 
(list 4800.5578 871.6333) 
(list 4800.5578 871.6436) 
(list 4800.5578 871.6539) 
(list 4800.5578 871.6642) 
(list 4800.5578 871.6744) 
(list 4800.5578 871.6847) 
(list 4800.5578 871.695) 
(list 4800.5578 871.7053) 
(list 4800.5578 871.7156) 
(list 4800.5578 871.7258) 
(list 4800.5578 871.7361) 
(list 4800.5578 871.7464) 
(list 4800.5578 871.7567) 
(list 4800.5578 871.7669) 
(list 4800.5578 871.7772) 
(list 4800.5578 871.7875) 
(list 4800.5578 871.7978) 
(list 4800.5578 871.8081) 
(list 4800.5578 871.8183) 
(list 4800.5578 871.8286) 
(list 4800.5578 871.8389) 
(list 4800.5578 871.8492) 
(list 4800.5578 871.8594) 
(list 4800.5578 871.8697) 
(list 4800.5578 871.88) 
(list 4801.136 871.88)))
(apply 'command (append '("pline") coords '("c")))
(setq tap15 (ssadd (entlast) tap15))
(command "_mirror" (entlast) "" "4800,900" "4800,901" "No")
(setq tap15 (ssadd (entlast) tap15))
(setq coords (list 
(list 4800 871.88) 
(list 4800.135 871.88) 
(list 4800.135 871.8903) 
(list 4800.135 871.9006) 
(list 4800.135 871.9108) 
(list 4800.135 871.9211) 
(list 4800.135 871.9314) 
(list 4800.135 871.9417) 
(list 4800.135 871.9519) 
(list 4800.135 871.9622) 
(list 4800.135 871.9725) 
(list 4800.135 871.9828) 
(list 4800.135 871.9931) 
(list 4800.135 872.0033) 
(list 4800.135 872.0136) 
(list 4800.135 872.0239) 
(list 4800.135 872.0342) 
(list 4800.135 872.0444) 
(list 4800.135 872.0547) 
(list 4800.135 872.065) 
(list 4800.135 872.0753) 
(list 4800.135 872.0856) 
(list 4800.135 872.0958) 
(list 4800.135 872.1061) 
(list 4800.135 872.1164) 
(list 4800.135 872.1267) 
(list 4800.135 872.1369) 
(list 4800.135 872.1472) 
(list 4800.135 872.1575) 
(list 4800.135 872.1678) 
(list 4800.135 872.1781) 
(list 4800.135 872.1883) 
(list 4800.135 872.1986) 
(list 4800.135 872.2089) 
(list 4800.135 872.2192) 
(list 4800.135 872.2294) 
(list 4800.135 872.2397) 
(list 4800.135 872.25) 
(list 4800 872.25)))
(apply 'command (append '("pline") coords '("c")))
(setq tap15 (ssadd (entlast) tap15))
(command "_mirror" (entlast) "" "4800,900" "4800,901" "No")
(setq tap15 (ssadd (entlast) tap15))
(setq coords (list 
(list 4800.568 871.88) 
(list 4800.5578 871.88) 
(list 4800.5562 871.8903) 
(list 4800.5507 871.9006) 
(list 4800.5417 871.9108) 
(list 4800.5292 871.9211) 
(list 4800.5138 871.9314) 
(list 4800.4958 871.9417) 
(list 4800.4757 871.9519) 
(list 4800.4543 871.9622) 
(list 4800.4321 871.9725) 
(list 4800.4098 871.9828) 
(list 4800.3881 871.9931) 
(list 4800.3677 872.0033) 
(list 4800.3492 872.0136) 
(list 4800.3331 872.0239) 
(list 4800.3199 872.0342) 
(list 4800.3102 872.0444) 
(list 4800.3041 872.0547) 
(list 4800.3019 872.065) 
(list 4800.3037 872.0753) 
(list 4800.3094 872.0856) 
(list 4800.3188 872.0958) 
(list 4800.3318 872.1061) 
(list 4800.3479 872.1164) 
(list 4800.3666 872.1267) 
(list 4800.3874 872.1369) 
(list 4800.4097 872.1472) 
(list 4800.4327 872.1575) 
(list 4800.4558 872.1678) 
(list 4800.4783 872.1781) 
(list 4800.4996 872.1883) 
(list 4800.5188 872.1986) 
(list 4800.5355 872.2089) 
(list 4800.5492 872.2192) 
(list 4800.5593 872.2294) 
(list 4800.5657 872.2397) 
(list 4800.568 872.25) 
(list 4800.568 872.25)))
(apply 'command (append '("pline") coords '("c")))
(setq tap15 (ssadd (entlast) tap15))
(command "_mirror" (entlast) "" "4800,900" "4800,901" "No")
(setq tap15 (ssadd (entlast) tap15))
(setq coords (list 
(list 4801.136 871.88) 
(list 4800.568 871.88) 
(list 4800.568 871.8903) 
(list 4800.568 871.9006) 
(list 4800.568 871.9108) 
(list 4800.568 871.9211) 
(list 4800.568 871.9314) 
(list 4800.568 871.9417) 
(list 4800.568 871.9519) 
(list 4800.568 871.9622) 
(list 4800.568 871.9725) 
(list 4800.568 871.9828) 
(list 4800.568 871.9931) 
(list 4800.568 872.0033) 
(list 4800.568 872.0136) 
(list 4800.568 872.0239) 
(list 4800.568 872.0342) 
(list 4800.568 872.0444) 
(list 4800.568 872.0547) 
(list 4800.568 872.065) 
(list 4800.568 872.0753) 
(list 4800.568 872.0856) 
(list 4800.568 872.0958) 
(list 4800.568 872.1061) 
(list 4800.568 872.1164) 
(list 4800.568 872.1267) 
(list 4800.568 872.1369) 
(list 4800.568 872.1472) 
(list 4800.568 872.1575) 
(list 4800.568 872.1678) 
(list 4800.568 872.1781) 
(list 4800.568 872.1883) 
(list 4800.568 872.1986) 
(list 4800.568 872.2089) 
(list 4800.568 872.2192) 
(list 4800.568 872.2294) 
(list 4800.568 872.2397) 
(list 4800.568 872.25) 
(list 4801.136 872.25)))
(apply 'command (append '("pline") coords '("c")))
(setq tap15 (ssadd (entlast) tap15))
(command "_mirror" (entlast) "" "4800,900" "4800,901" "No")
(setq tap15 (ssadd (entlast) tap15))
(command "_block" "blktap15" "4800,900" tap15 "")
(command "_insert" "blktap15" "4800,900" "1" "1" "0")
(command "_insert" "blktap15" "4800,900" "1" "1" "180")
(setq uc15 nil)
(setq uc15 (ssadd))
(setq coords (list 
(list 0 -0.185) 
(list 0.135 -0.185) 
(list 0.135 -0.17472) 
(list 0.135 -0.16444) 
(list 0.135 -0.15417) 
(list 0.135 -0.14389) 
(list 0.135 -0.13361) 
(list 0.135 -0.12333) 
(list 0.135 -0.11306) 
(list 0.135 -0.10278) 
(list 0.135 -0.0925) 
(list 0.135 -0.082222) 
(list 0.135 -0.071944) 
(list 0.135 -0.061667) 
(list 0.135 -0.051389) 
(list 0.135 -0.041111) 
(list 0.135 -0.030833) 
(list 0.135 -0.020556) 
(list 0.135 -0.010278) 
(list 0.135 0) 
(list 0.135 0.010278) 
(list 0.135 0.020556) 
(list 0.135 0.030833) 
(list 0.135 0.041111) 
(list 0.135 0.051389) 
(list 0.135 0.061667) 
(list 0.135 0.071944) 
(list 0.135 0.082222) 
(list 0.135 0.0925) 
(list 0.135 0.10278) 
(list 0.135 0.11306) 
(list 0.135 0.12333) 
(list 0.135 0.13361) 
(list 0.135 0.14389) 
(list 0.135 0.15417) 
(list 0.135 0.16444) 
(list 0.135 0.17472) 
(list 0.135 0.185) 
(list 0 0.185)))
(apply 'command (append '("pline") coords '("c")))
(setq uc15 (ssadd (entlast) uc15))
(setq coords (list 
(list 1.136 -0.185) 
(list 0.568 -0.185) 
(list 0.56595 -0.17472) 
(list 0.55986 -0.16444) 
(list 0.54991 -0.15417) 
(list 0.53642 -0.14389) 
(list 0.51978 -0.13361) 
(list 0.5005 -0.12333) 
(list 0.47917 -0.11306) 
(list 0.45644 -0.10278) 
(list 0.433 -0.0925) 
(list 0.40956 -0.082222) 
(list 0.38683 -0.071944) 
(list 0.3655 -0.061667) 
(list 0.34622 -0.051389) 
(list 0.32958 -0.041111) 
(list 0.31609 -0.030833) 
(list 0.30614 -0.020556) 
(list 0.30005 -0.010278) 
(list 0.298 0) 
(list 0.30005 0.010278) 
(list 0.30614 0.020556) 
(list 0.31609 0.030833) 
(list 0.32958 0.041111) 
(list 0.34622 0.051389) 
(list 0.3655 0.061667) 
(list 0.38683 0.071944) 
(list 0.40956 0.082222) 
(list 0.433 0.0925) 
(list 0.45644 0.10278) 
(list 0.47917 0.11306) 
(list 0.5005 0.12333) 
(list 0.51978 0.13361) 
(list 0.53642 0.14389) 
(list 0.54991 0.15417) 
(list 0.55986 0.16444) 
(list 0.56595 0.17472) 
(list 0.568 0.185) 
(list 1.136 0.185)))
(apply 'command (append '("pline") coords '("c")))
(setq uc15 (ssadd (entlast) uc15))
(command "_block" "blkuc15" "0,0.185" uc15 "")
(command "_insert" "blkuc15" "4800,872.62" "1" "1" "0")
(command "_insert" "blkuc15" "4800,872.25" "1" "1" "180")
(command "_insert" "blkuc15" "4800,872.99" "1" "1" "0")
(command "_insert" "blkuc15" "4800,872.62" "1" "1" "180")
(command "_insert" "blkuc15" "4800,873.36" "1" "1" "0")
(command "_insert" "blkuc15" "4800,872.99" "1" "1" "180")
(command "_insert" "blkuc15" "4800,873.73" "1" "1" "0")
(command "_insert" "blkuc15" "4800,873.36" "1" "1" "180")
(command "_insert" "blkuc15" "4800,874.1" "1" "1" "0")
(command "_insert" "blkuc15" "4800,873.73" "1" "1" "180")
(command "_insert" "blkuc15" "4800,874.47" "1" "1" "0")
(command "_insert" "blkuc15" "4800,874.1" "1" "1" "180")
(command "_insert" "blkuc15" "4800,874.84" "1" "1" "0")
(command "_insert" "blkuc15" "4800,874.47" "1" "1" "180")
(command "_insert" "blkuc15" "4800,875.21" "1" "1" "0")
(command "_insert" "blkuc15" "4800,874.84" "1" "1" "180")
(command "_insert" "blkuc15" "4800,875.58" "1" "1" "0")
(command "_insert" "blkuc15" "4800,875.21" "1" "1" "180")
(command "_insert" "blkuc15" "4800,875.95" "1" "1" "0")
(command "_insert" "blkuc15" "4800,875.58" "1" "1" "180")
(command "_insert" "blkuc15" "4800,876.32" "1" "1" "0")
(command "_insert" "blkuc15" "4800,875.95" "1" "1" "180")
(command "_insert" "blkuc15" "4800,876.69" "1" "1" "0")
(command "_insert" "blkuc15" "4800,876.32" "1" "1" "180")
(command "_insert" "blkuc15" "4800,877.06" "1" "1" "0")
(command "_insert" "blkuc15" "4800,876.69" "1" "1" "180")
(command "_insert" "blkuc15" "4800,877.43" "1" "1" "0")
(command "_insert" "blkuc15" "4800,877.06" "1" "1" "180")
(command "_insert" "blkuc15" "4800,877.8" "1" "1" "0")
(command "_insert" "blkuc15" "4800,877.43" "1" "1" "180")
(command "_insert" "blkuc15" "4800,878.17" "1" "1" "0")
(command "_insert" "blkuc15" "4800,877.8" "1" "1" "180")
(command "_insert" "blkuc15" "4800,878.54" "1" "1" "0")
(command "_insert" "blkuc15" "4800,878.17" "1" "1" "180")
(command "_insert" "blkuc15" "4800,878.91" "1" "1" "0")
(command "_insert" "blkuc15" "4800,878.54" "1" "1" "180")
(command "_insert" "blkuc15" "4800,879.28" "1" "1" "0")
(command "_insert" "blkuc15" "4800,878.91" "1" "1" "180")
(command "_insert" "blkuc15" "4800,879.65" "1" "1" "0")
(command "_insert" "blkuc15" "4800,879.28" "1" "1" "180")
(command "_insert" "blkuc15" "4800,880.02" "1" "1" "0")
(command "_insert" "blkuc15" "4800,879.65" "1" "1" "180")
(command "_insert" "blkuc15" "4800,880.39" "1" "1" "0")
(command "_insert" "blkuc15" "4800,880.02" "1" "1" "180")
(command "_insert" "blkuc15" "4800,880.76" "1" "1" "0")
(command "_insert" "blkuc15" "4800,880.39" "1" "1" "180")
(command "_insert" "blkuc15" "4800,881.13" "1" "1" "0")
(command "_insert" "blkuc15" "4800,880.76" "1" "1" "180")
(command "_insert" "blkuc15" "4800,881.5" "1" "1" "0")
(command "_insert" "blkuc15" "4800,881.13" "1" "1" "180")
(command "_insert" "blkuc15" "4800,881.87" "1" "1" "0")
(command "_insert" "blkuc15" "4800,881.5" "1" "1" "180")
(command "_insert" "blkuc15" "4800,882.24" "1" "1" "0")
(command "_insert" "blkuc15" "4800,881.87" "1" "1" "180")
(command "_insert" "blkuc15" "4800,882.61" "1" "1" "0")
(command "_insert" "blkuc15" "4800,882.24" "1" "1" "180")
(command "_insert" "blkuc15" "4800,882.98" "1" "1" "0")
(command "_insert" "blkuc15" "4800,882.61" "1" "1" "180")
(command "_insert" "blkuc15" "4800,883.35" "1" "1" "0")
(command "_insert" "blkuc15" "4800,882.98" "1" "1" "180")
(command "_insert" "blkuc15" "4800,883.72" "1" "1" "0")
(command "_insert" "blkuc15" "4800,883.35" "1" "1" "180")
(command "_insert" "blkuc15" "4800,884.09" "1" "1" "0")
(command "_insert" "blkuc15" "4800,883.72" "1" "1" "180")
(command "_insert" "blkuc15" "4800,884.46" "1" "1" "0")
(command "_insert" "blkuc15" "4800,884.09" "1" "1" "180")
(command "_insert" "blkuc15" "4800,884.83" "1" "1" "0")
(command "_insert" "blkuc15" "4800,884.46" "1" "1" "180")
(command "_insert" "blkuc15" "4800,885.2" "1" "1" "0")
(command "_insert" "blkuc15" "4800,884.83" "1" "1" "180")
(command "_insert" "blkuc15" "4800,885.57" "1" "1" "0")
(command "_insert" "blkuc15" "4800,885.2" "1" "1" "180")
(command "_insert" "blkuc15" "4800,885.94" "1" "1" "0")
(command "_insert" "blkuc15" "4800,885.57" "1" "1" "180")
(command "_insert" "blkuc15" "4800,886.31" "1" "1" "0")
(command "_insert" "blkuc15" "4800,885.94" "1" "1" "180")
(command "_insert" "blkuc15" "4800,886.68" "1" "1" "0")
(command "_insert" "blkuc15" "4800,886.31" "1" "1" "180")
(command "_insert" "blkuc15" "4800,887.05" "1" "1" "0")
(command "_insert" "blkuc15" "4800,886.68" "1" "1" "180")
(command "_insert" "blkuc15" "4800,887.42" "1" "1" "0")
(command "_insert" "blkuc15" "4800,887.05" "1" "1" "180")
(command "_insert" "blkuc15" "4800,887.79" "1" "1" "0")
(command "_insert" "blkuc15" "4800,887.42" "1" "1" "180")
(command "_insert" "blkuc15" "4800,888.16" "1" "1" "0")
(command "_insert" "blkuc15" "4800,887.79" "1" "1" "180")
(command "_insert" "blkuc15" "4800,888.53" "1" "1" "0")
(command "_insert" "blkuc15" "4800,888.16" "1" "1" "180")
(command "_insert" "blkuc15" "4800,888.9" "1" "1" "0")
(command "_insert" "blkuc15" "4800,888.53" "1" "1" "180")
(command "_insert" "blkuc15" "4800,889.27" "1" "1" "0")
(command "_insert" "blkuc15" "4800,888.9" "1" "1" "180")
(command "_insert" "blkuc15" "4800,889.64" "1" "1" "0")
(command "_insert" "blkuc15" "4800,889.27" "1" "1" "180")
(command "_insert" "blkuc15" "4800,890.01" "1" "1" "0")
(command "_insert" "blkuc15" "4800,889.64" "1" "1" "180")
(command "_insert" "blkuc15" "4800,890.38" "1" "1" "0")
(command "_insert" "blkuc15" "4800,890.01" "1" "1" "180")
(command "_insert" "blkuc15" "4800,890.75" "1" "1" "0")
(command "_insert" "blkuc15" "4800,890.38" "1" "1" "180")
(command "_insert" "blkuc15" "4800,891.12" "1" "1" "0")
(command "_insert" "blkuc15" "4800,890.75" "1" "1" "180")
(command "_insert" "blkuc15" "4800,891.49" "1" "1" "0")
(command "_insert" "blkuc15" "4800,891.12" "1" "1" "180")
(command "_insert" "blkuc15" "4800,891.86" "1" "1" "0")
(command "_insert" "blkuc15" "4800,891.49" "1" "1" "180")
(command "_insert" "blkuc15" "4800,892.23" "1" "1" "0")
(command "_insert" "blkuc15" "4800,891.86" "1" "1" "180")
(command "_insert" "blkuc15" "4800,892.6" "1" "1" "0")
(command "_insert" "blkuc15" "4800,892.23" "1" "1" "180")
(command "_insert" "blkuc15" "4800,892.97" "1" "1" "0")
(command "_insert" "blkuc15" "4800,892.6" "1" "1" "180")
(command "_insert" "blkuc15" "4800,893.34" "1" "1" "0")
(command "_insert" "blkuc15" "4800,892.97" "1" "1" "180")
(command "_insert" "blkuc15" "4800,893.71" "1" "1" "0")
(command "_insert" "blkuc15" "4800,893.34" "1" "1" "180")
(command "_insert" "blkuc15" "4800,894.08" "1" "1" "0")
(command "_insert" "blkuc15" "4800,893.71" "1" "1" "180")
(command "_insert" "blkuc15" "4800,894.45" "1" "1" "0")
(command "_insert" "blkuc15" "4800,894.08" "1" "1" "180")
(command "_insert" "blkuc15" "4800,894.82" "1" "1" "0")
(command "_insert" "blkuc15" "4800,894.45" "1" "1" "180")
(command "_insert" "blkuc15" "4800,895.19" "1" "1" "0")
(command "_insert" "blkuc15" "4800,894.82" "1" "1" "180")
(command "_insert" "blkuc15" "4800,895.56" "1" "1" "0")
(command "_insert" "blkuc15" "4800,895.19" "1" "1" "180")
(command "_insert" "blkuc15" "4800,895.93" "1" "1" "0")
(command "_insert" "blkuc15" "4800,895.56" "1" "1" "180")
(command "_insert" "blkuc15" "4800,896.3" "1" "1" "0")
(command "_insert" "blkuc15" "4800,895.93" "1" "1" "180")
(command "_insert" "blkuc15" "4800,896.67" "1" "1" "0")
(command "_insert" "blkuc15" "4800,896.3" "1" "1" "180")
(command "_insert" "blkuc15" "4800,897.04" "1" "1" "0")
(command "_insert" "blkuc15" "4800,896.67" "1" "1" "180")
(command "_insert" "blkuc15" "4800,897.41" "1" "1" "0")
(command "_insert" "blkuc15" "4800,897.04" "1" "1" "180")
(command "_insert" "blkuc15" "4800,897.78" "1" "1" "0")
(command "_insert" "blkuc15" "4800,897.41" "1" "1" "180")
(command "_insert" "blkuc15" "4800,898.15" "1" "1" "0")
(command "_insert" "blkuc15" "4800,897.78" "1" "1" "180")
(command "_insert" "blkuc15" "4800,898.52" "1" "1" "0")
(command "_insert" "blkuc15" "4800,898.15" "1" "1" "180")
(command "_insert" "blkuc15" "4800,898.89" "1" "1" "0")
(command "_insert" "blkuc15" "4800,898.52" "1" "1" "180")
(command "_insert" "blkuc15" "4800,899.26" "1" "1" "0")
(command "_insert" "blkuc15" "4800,898.89" "1" "1" "180")
(command "_insert" "blkuc15" "4800,899.63" "1" "1" "0")
(command "_insert" "blkuc15" "4800,899.26" "1" "1" "180")
(command "_insert" "blkuc15" "4800,900" "1" "1" "0")
(command "_insert" "blkuc15" "4800,899.63" "1" "1" "180")
(command "_insert" "blkuc15" "4800,900.37" "1" "1" "0")
(command "_insert" "blkuc15" "4800,900" "1" "1" "180")
(command "_insert" "blkuc15" "4800,900.74" "1" "1" "0")
(command "_insert" "blkuc15" "4800,900.37" "1" "1" "180")
(command "_insert" "blkuc15" "4800,901.11" "1" "1" "0")
(command "_insert" "blkuc15" "4800,900.74" "1" "1" "180")
(command "_insert" "blkuc15" "4800,901.48" "1" "1" "0")
(command "_insert" "blkuc15" "4800,901.11" "1" "1" "180")
(command "_insert" "blkuc15" "4800,901.85" "1" "1" "0")
(command "_insert" "blkuc15" "4800,901.48" "1" "1" "180")
(command "_insert" "blkuc15" "4800,902.22" "1" "1" "0")
(command "_insert" "blkuc15" "4800,901.85" "1" "1" "180")
(command "_insert" "blkuc15" "4800,902.59" "1" "1" "0")
(command "_insert" "blkuc15" "4800,902.22" "1" "1" "180")
(command "_insert" "blkuc15" "4800,902.96" "1" "1" "0")
(command "_insert" "blkuc15" "4800,902.59" "1" "1" "180")
(command "_insert" "blkuc15" "4800,903.33" "1" "1" "0")
(command "_insert" "blkuc15" "4800,902.96" "1" "1" "180")
(command "_insert" "blkuc15" "4800,903.7" "1" "1" "0")
(command "_insert" "blkuc15" "4800,903.33" "1" "1" "180")
(command "_insert" "blkuc15" "4800,904.07" "1" "1" "0")
(command "_insert" "blkuc15" "4800,903.7" "1" "1" "180")
(command "_insert" "blkuc15" "4800,904.44" "1" "1" "0")
(command "_insert" "blkuc15" "4800,904.07" "1" "1" "180")
(command "_insert" "blkuc15" "4800,904.81" "1" "1" "0")
(command "_insert" "blkuc15" "4800,904.44" "1" "1" "180")
(command "_insert" "blkuc15" "4800,905.18" "1" "1" "0")
(command "_insert" "blkuc15" "4800,904.81" "1" "1" "180")
(command "_insert" "blkuc15" "4800,905.55" "1" "1" "0")
(command "_insert" "blkuc15" "4800,905.18" "1" "1" "180")
(command "_insert" "blkuc15" "4800,905.92" "1" "1" "0")
(command "_insert" "blkuc15" "4800,905.55" "1" "1" "180")
(command "_insert" "blkuc15" "4800,906.29" "1" "1" "0")
(command "_insert" "blkuc15" "4800,905.92" "1" "1" "180")
(command "_insert" "blkuc15" "4800,906.66" "1" "1" "0")
(command "_insert" "blkuc15" "4800,906.29" "1" "1" "180")
(command "_insert" "blkuc15" "4800,907.03" "1" "1" "0")
(command "_insert" "blkuc15" "4800,906.66" "1" "1" "180")
(command "_insert" "blkuc15" "4800,907.4" "1" "1" "0")
(command "_insert" "blkuc15" "4800,907.03" "1" "1" "180")
(command "_insert" "blkuc15" "4800,907.77" "1" "1" "0")
(command "_insert" "blkuc15" "4800,907.4" "1" "1" "180")
(command "_insert" "blkuc15" "4800,908.14" "1" "1" "0")
(command "_insert" "blkuc15" "4800,907.77" "1" "1" "180")
(command "_insert" "blkuc15" "4800,908.51" "1" "1" "0")
(command "_insert" "blkuc15" "4800,908.14" "1" "1" "180")
(command "_insert" "blkuc15" "4800,908.88" "1" "1" "0")
(command "_insert" "blkuc15" "4800,908.51" "1" "1" "180")
(command "_insert" "blkuc15" "4800,909.25" "1" "1" "0")
(command "_insert" "blkuc15" "4800,908.88" "1" "1" "180")
(command "_insert" "blkuc15" "4800,909.62" "1" "1" "0")
(command "_insert" "blkuc15" "4800,909.25" "1" "1" "180")
(command "_insert" "blkuc15" "4800,909.99" "1" "1" "0")
(command "_insert" "blkuc15" "4800,909.62" "1" "1" "180")
(command "_insert" "blkuc15" "4800,910.36" "1" "1" "0")
(command "_insert" "blkuc15" "4800,909.99" "1" "1" "180")
(command "_insert" "blkuc15" "4800,910.73" "1" "1" "0")
(command "_insert" "blkuc15" "4800,910.36" "1" "1" "180")
(command "_insert" "blkuc15" "4800,911.1" "1" "1" "0")
(command "_insert" "blkuc15" "4800,910.73" "1" "1" "180")
(command "_insert" "blkuc15" "4800,911.47" "1" "1" "0")
(command "_insert" "blkuc15" "4800,911.1" "1" "1" "180")
(command "_insert" "blkuc15" "4800,911.84" "1" "1" "0")
(command "_insert" "blkuc15" "4800,911.47" "1" "1" "180")
(command "_insert" "blkuc15" "4800,912.21" "1" "1" "0")
(command "_insert" "blkuc15" "4800,911.84" "1" "1" "180")
(command "_insert" "blkuc15" "4800,912.58" "1" "1" "0")
(command "_insert" "blkuc15" "4800,912.21" "1" "1" "180")
(command "_insert" "blkuc15" "4800,912.95" "1" "1" "0")
(command "_insert" "blkuc15" "4800,912.58" "1" "1" "180")
(command "_insert" "blkuc15" "4800,913.32" "1" "1" "0")
(command "_insert" "blkuc15" "4800,912.95" "1" "1" "180")
(command "_insert" "blkuc15" "4800,913.69" "1" "1" "0")
(command "_insert" "blkuc15" "4800,913.32" "1" "1" "180")
(command "_insert" "blkuc15" "4800,914.06" "1" "1" "0")
(command "_insert" "blkuc15" "4800,913.69" "1" "1" "180")
(command "_insert" "blkuc15" "4800,914.43" "1" "1" "0")
(command "_insert" "blkuc15" "4800,914.06" "1" "1" "180")
(command "_insert" "blkuc15" "4800,914.8" "1" "1" "0")
(command "_insert" "blkuc15" "4800,914.43" "1" "1" "180")
(command "_insert" "blkuc15" "4800,915.17" "1" "1" "0")
(command "_insert" "blkuc15" "4800,914.8" "1" "1" "180")
(command "_insert" "blkuc15" "4800,915.54" "1" "1" "0")
(command "_insert" "blkuc15" "4800,915.17" "1" "1" "180")
(command "_insert" "blkuc15" "4800,915.91" "1" "1" "0")
(command "_insert" "blkuc15" "4800,915.54" "1" "1" "180")
(command "_insert" "blkuc15" "4800,916.28" "1" "1" "0")
(command "_insert" "blkuc15" "4800,915.91" "1" "1" "180")
(command "_insert" "blkuc15" "4800,916.65" "1" "1" "0")
(command "_insert" "blkuc15" "4800,916.28" "1" "1" "180")
(command "_insert" "blkuc15" "4800,917.02" "1" "1" "0")
(command "_insert" "blkuc15" "4800,916.65" "1" "1" "180")
(command "_insert" "blkuc15" "4800,917.39" "1" "1" "0")
(command "_insert" "blkuc15" "4800,917.02" "1" "1" "180")
(command "_insert" "blkuc15" "4800,917.76" "1" "1" "0")
(command "_insert" "blkuc15" "4800,917.39" "1" "1" "180")
(command "_insert" "blkuc15" "4800,918.13" "1" "1" "0")
(command "_insert" "blkuc15" "4800,917.76" "1" "1" "180")
(command "_insert" "blkuc15" "4800,918.5" "1" "1" "0")
(command "_insert" "blkuc15" "4800,918.13" "1" "1" "180")
(command "_insert" "blkuc15" "4800,918.87" "1" "1" "0")
(command "_insert" "blkuc15" "4800,918.5" "1" "1" "180")
(command "_insert" "blkuc15" "4800,919.24" "1" "1" "0")
(command "_insert" "blkuc15" "4800,918.87" "1" "1" "180")
(command "_insert" "blkuc15" "4800,919.61" "1" "1" "0")
(command "_insert" "blkuc15" "4800,919.24" "1" "1" "180")
(command "_insert" "blkuc15" "4800,919.98" "1" "1" "0")
(command "_insert" "blkuc15" "4800,919.61" "1" "1" "180")
(command "_insert" "blkuc15" "4800,920.35" "1" "1" "0")
(command "_insert" "blkuc15" "4800,919.98" "1" "1" "180")
(command "_insert" "blkuc15" "4800,920.72" "1" "1" "0")
(command "_insert" "blkuc15" "4800,920.35" "1" "1" "180")
(command "_insert" "blkuc15" "4800,921.09" "1" "1" "0")
(command "_insert" "blkuc15" "4800,920.72" "1" "1" "180")
(command "_insert" "blkuc15" "4800,921.46" "1" "1" "0")
(command "_insert" "blkuc15" "4800,921.09" "1" "1" "180")
(command "_insert" "blkuc15" "4800,921.83" "1" "1" "0")
(command "_insert" "blkuc15" "4800,921.46" "1" "1" "180")
(command "_insert" "blkuc15" "4800,922.2" "1" "1" "0")
(command "_insert" "blkuc15" "4800,921.83" "1" "1" "180")
(command "_insert" "blkuc15" "4800,922.57" "1" "1" "0")
(command "_insert" "blkuc15" "4800,922.2" "1" "1" "180")
(command "_insert" "blkuc15" "4800,922.94" "1" "1" "0")
(command "_insert" "blkuc15" "4800,922.57" "1" "1" "180")
(command "_insert" "blkuc15" "4800,923.31" "1" "1" "0")
(command "_insert" "blkuc15" "4800,922.94" "1" "1" "180")
(command "_insert" "blkuc15" "4800,923.68" "1" "1" "0")
(command "_insert" "blkuc15" "4800,923.31" "1" "1" "180")
(command "_insert" "blkuc15" "4800,924.05" "1" "1" "0")
(command "_insert" "blkuc15" "4800,923.68" "1" "1" "180")
(command "_insert" "blkuc15" "4800,924.42" "1" "1" "0")
(command "_insert" "blkuc15" "4800,924.05" "1" "1" "180")
(command "_insert" "blkuc15" "4800,924.79" "1" "1" "0")
(command "_insert" "blkuc15" "4800,924.42" "1" "1" "180")
(command "_insert" "blkuc15" "4800,925.16" "1" "1" "0")
(command "_insert" "blkuc15" "4800,924.79" "1" "1" "180")
(command "_insert" "blkuc15" "4800,925.53" "1" "1" "0")
(command "_insert" "blkuc15" "4800,925.16" "1" "1" "180")
(command "_insert" "blkuc15" "4800,925.9" "1" "1" "0")
(command "_insert" "blkuc15" "4800,925.53" "1" "1" "180")
(command "_insert" "blkuc15" "4800,926.27" "1" "1" "0")
(command "_insert" "blkuc15" "4800,925.9" "1" "1" "180")
(command "_insert" "blkuc15" "4800,926.64" "1" "1" "0")
(command "_insert" "blkuc15" "4800,926.27" "1" "1" "180")
(command "_insert" "blkuc15" "4800,927.01" "1" "1" "0")
(command "_insert" "blkuc15" "4800,926.64" "1" "1" "180")
(command "_insert" "blkuc15" "4800,927.38" "1" "1" "0")
(command "_insert" "blkuc15" "4800,927.01" "1" "1" "180")
(command "_insert" "blkuc15" "4800,927.75" "1" "1" "0")
(command "_insert" "blkuc15" "4800,927.38" "1" "1" "180")
(command "_layer" "set" "phccover" "")
(command "_rectangle" "4798.864,933.3" "4801.136,866.7")
(command "_layer" "set" "nitride" "")
(setq phc15 currobj)
(command "_layer" "set" "cover" "")
(command "_rectangle" "4798.864,836.7" "4801.136,963.3")
(command "_layer" "set" "nitride" "")
(command "_layer" "set" "text" "")
(command "_circle" "4797.914,846.7" "0.075")
(command "_circle" "4797.539,846.7" "0.15")
(command "_circle" "4797.164,846.7" "0.075")
(command "_circle" "4796.789,846.7" "0.15")
(command "_circle" "4797.914,848.7" "0.075")
(command "_circle" "4797.539,848.7" "0.075")
(command "_circle" "4797.164,848.7" "0.15")
(command "_circle" "4796.789,848.7" "0.15")
(command "_circle" "4797.914,850.7" "0.075")
(command "_circle" "4797.539,850.7" "0.15")
(command "_circle" "4797.164,850.7" "0.15")
(command "_circle" "4796.789,850.7" "0.15")
(command "_circle" "4797.914,852.7" "0.075")
(command "_circle" "4797.539,852.7" "0.075")
(command "_circle" "4797.164,852.7" "0.075")
(command "_circle" "4796.789,852.7" "0.075")
(command "_circle" "4796.414,852.7" "0.15")
(command "_circle" "4797.914,854.7" "0.075")
(command "_circle" "4797.539,854.7" "0.15")
(command "_circle" "4797.164,854.7" "0.075")
(command "_circle" "4796.789,854.7" "0.075")
(command "_circle" "4796.414,854.7" "0.15")
(command "_circle" "4797.914,856.7" "0.075")
(command "_circle" "4797.539,856.7" "0.075")
(command "_circle" "4797.164,856.7" "0.15")
(command "_circle" "4796.789,856.7" "0.075")
(command "_circle" "4796.414,856.7" "0.15")
(command "_circle" "4797.914,858.7" "0.075")
(command "_circle" "4797.539,858.7" "0.15")
(command "_circle" "4797.164,858.7" "0.15")
(command "_circle" "4796.789,858.7" "0.075")
(command "_circle" "4796.414,858.7" "0.15")
(command "_circle" "4797.914,860.7" "0.075")
(command "_circle" "4797.539,860.7" "0.075")
(command "_circle" "4797.164,860.7" "0.075")
(command "_circle" "4796.789,860.7" "0.15")
(command "_circle" "4796.414,860.7" "0.15")
(command "_circle" "4797.914,862.7" "0.075")
(command "_circle" "4797.539,862.7" "0.15")
(command "_circle" "4797.164,862.7" "0.075")
(command "_circle" "4796.789,862.7" "0.15")
(command "_circle" "4796.414,862.7" "0.15")
(command "_circle" "4797.914,864.7" "0.075")
(command "_circle" "4797.539,864.7" "0.075")
(command "_circle" "4797.164,864.7" "0.15")
(command "_circle" "4796.789,864.7" "0.15")
(command "_circle" "4796.414,864.7" "0.15")
(command "_circle" "4797.914,866.7" "0.075")
(command "_circle" "4797.539,866.7" "0.15")
(command "_circle" "4797.164,866.7" "0.15")
(command "_circle" "4796.789,866.7" "0.15")
(command "_circle" "4796.414,866.7" "0.15")
(command "_circle" "4797.914,868.7" "0.075")
(command "_circle" "4797.539,868.7" "0.075")
(command "_circle" "4797.164,868.7" "0.075")
(command "_circle" "4796.789,868.7" "0.075")
(command "_circle" "4796.414,868.7" "0.075")
(command "_circle" "4796.039,868.7" "0.15")
(command "_circle" "4797.914,870.7" "0.075")
(command "_circle" "4797.539,870.7" "0.15")
(command "_circle" "4797.164,870.7" "0.075")
(command "_circle" "4796.789,870.7" "0.075")
(command "_circle" "4796.414,870.7" "0.075")
(command "_circle" "4796.039,870.7" "0.15")
(command "_circle" "4797.914,872.7" "0.075")
(command "_circle" "4797.539,872.7" "0.075")
(command "_circle" "4797.164,872.7" "0.15")
(command "_circle" "4796.789,872.7" "0.075")
(command "_circle" "4796.414,872.7" "0.075")
(command "_circle" "4796.039,872.7" "0.15")
(command "_circle" "4797.914,874.7" "0.075")
(command "_circle" "4797.539,874.7" "0.15")
(command "_circle" "4797.164,874.7" "0.15")
(command "_circle" "4796.789,874.7" "0.075")
(command "_circle" "4796.414,874.7" "0.075")
(command "_circle" "4796.039,874.7" "0.15")
(command "_circle" "4797.914,876.7" "0.075")
(command "_circle" "4797.539,876.7" "0.075")
(command "_circle" "4797.164,876.7" "0.075")
(command "_circle" "4796.789,876.7" "0.15")
(command "_circle" "4796.414,876.7" "0.075")
(command "_circle" "4796.039,876.7" "0.15")
(command "_circle" "4797.914,878.7" "0.075")
(command "_circle" "4797.539,878.7" "0.15")
(command "_circle" "4797.164,878.7" "0.075")
(command "_circle" "4796.789,878.7" "0.15")
(command "_circle" "4796.414,878.7" "0.075")
(command "_circle" "4796.039,878.7" "0.15")
(command "_circle" "4797.914,880.7" "0.075")
(command "_circle" "4797.539,880.7" "0.075")
(command "_circle" "4797.164,880.7" "0.15")
(command "_circle" "4796.789,880.7" "0.15")
(command "_circle" "4796.414,880.7" "0.075")
(command "_circle" "4796.039,880.7" "0.15")
(command "_circle" "4797.914,882.7" "0.075")
(command "_circle" "4797.539,882.7" "0.15")
(command "_circle" "4797.164,882.7" "0.15")
(command "_circle" "4796.789,882.7" "0.15")
(command "_circle" "4796.414,882.7" "0.075")
(command "_circle" "4796.039,882.7" "0.15")
(command "_circle" "4797.914,884.7" "0.075")
(command "_circle" "4797.539,884.7" "0.075")
(command "_circle" "4797.164,884.7" "0.075")
(command "_circle" "4796.789,884.7" "0.075")
(command "_circle" "4796.414,884.7" "0.15")
(command "_circle" "4796.039,884.7" "0.15")
(command "_circle" "4797.914,886.7" "0.075")
(command "_circle" "4797.539,886.7" "0.15")
(command "_circle" "4797.164,886.7" "0.075")
(command "_circle" "4796.789,886.7" "0.075")
(command "_circle" "4796.414,886.7" "0.15")
(command "_circle" "4796.039,886.7" "0.15")
(command "_circle" "4797.914,888.7" "0.075")
(command "_circle" "4797.539,888.7" "0.075")
(command "_circle" "4797.164,888.7" "0.15")
(command "_circle" "4796.789,888.7" "0.075")
(command "_circle" "4796.414,888.7" "0.15")
(command "_circle" "4796.039,888.7" "0.15")
(command "_circle" "4797.914,890.7" "0.075")
(command "_circle" "4797.539,890.7" "0.15")
(command "_circle" "4797.164,890.7" "0.15")
(command "_circle" "4796.789,890.7" "0.075")
(command "_circle" "4796.414,890.7" "0.15")
(command "_circle" "4796.039,890.7" "0.15")
(command "_circle" "4797.914,892.7" "0.075")
(command "_circle" "4797.539,892.7" "0.075")
(command "_circle" "4797.164,892.7" "0.075")
(command "_circle" "4796.789,892.7" "0.15")
(command "_circle" "4796.414,892.7" "0.15")
(command "_circle" "4796.039,892.7" "0.15")
(command "_circle" "4797.914,894.7" "0.075")
(command "_circle" "4797.539,894.7" "0.15")
(command "_circle" "4797.164,894.7" "0.075")
(command "_circle" "4796.789,894.7" "0.15")
(command "_circle" "4796.414,894.7" "0.15")
(command "_circle" "4796.039,894.7" "0.15")
(command "_circle" "4797.914,896.7" "0.075")
(command "_circle" "4797.539,896.7" "0.075")
(command "_circle" "4797.164,896.7" "0.15")
(command "_circle" "4796.789,896.7" "0.15")
(command "_circle" "4796.414,896.7" "0.15")
(command "_circle" "4796.039,896.7" "0.15")
(command "_circle" "4797.914,898.7" "0.075")
(command "_circle" "4797.539,898.7" "0.15")
(command "_circle" "4797.164,898.7" "0.15")
(command "_circle" "4796.789,898.7" "0.15")
(command "_circle" "4796.414,898.7" "0.15")
(command "_circle" "4796.039,898.7" "0.15")
(command "_circle" "4797.914,900.7" "0.075")
(command "_circle" "4797.539,900.7" "0.075")
(command "_circle" "4797.164,900.7" "0.075")
(command "_circle" "4796.789,900.7" "0.075")
(command "_circle" "4796.414,900.7" "0.075")
(command "_circle" "4796.039,900.7" "0.075")
(command "_circle" "4795.664,900.7" "0.15")
(command "_circle" "4797.914,902.7" "0.075")
(command "_circle" "4797.539,902.7" "0.15")
(command "_circle" "4797.164,902.7" "0.075")
(command "_circle" "4796.789,902.7" "0.075")
(command "_circle" "4796.414,902.7" "0.075")
(command "_circle" "4796.039,902.7" "0.075")
(command "_circle" "4795.664,902.7" "0.15")
(command "_circle" "4797.914,904.7" "0.075")
(command "_circle" "4797.539,904.7" "0.075")
(command "_circle" "4797.164,904.7" "0.15")
(command "_circle" "4796.789,904.7" "0.075")
(command "_circle" "4796.414,904.7" "0.075")
(command "_circle" "4796.039,904.7" "0.075")
(command "_circle" "4795.664,904.7" "0.15")
(command "_circle" "4797.914,906.7" "0.075")
(command "_circle" "4797.539,906.7" "0.15")
(command "_circle" "4797.164,906.7" "0.15")
(command "_circle" "4796.789,906.7" "0.075")
(command "_circle" "4796.414,906.7" "0.075")
(command "_circle" "4796.039,906.7" "0.075")
(command "_circle" "4795.664,906.7" "0.15")
(command "_circle" "4797.914,908.7" "0.075")
(command "_circle" "4797.539,908.7" "0.075")
(command "_circle" "4797.164,908.7" "0.075")
(command "_circle" "4796.789,908.7" "0.15")
(command "_circle" "4796.414,908.7" "0.075")
(command "_circle" "4796.039,908.7" "0.075")
(command "_circle" "4795.664,908.7" "0.15")
(command "_circle" "4797.914,910.7" "0.075")
(command "_circle" "4797.539,910.7" "0.15")
(command "_circle" "4797.164,910.7" "0.075")
(command "_circle" "4796.789,910.7" "0.15")
(command "_circle" "4796.414,910.7" "0.075")
(command "_circle" "4796.039,910.7" "0.075")
(command "_circle" "4795.664,910.7" "0.15")
(command "_circle" "4797.914,912.7" "0.075")
(command "_circle" "4797.539,912.7" "0.075")
(command "_circle" "4797.164,912.7" "0.15")
(command "_circle" "4796.789,912.7" "0.15")
(command "_circle" "4796.414,912.7" "0.075")
(command "_circle" "4796.039,912.7" "0.075")
(command "_circle" "4795.664,912.7" "0.15")
(command "_circle" "4797.914,914.7" "0.075")
(command "_circle" "4797.539,914.7" "0.15")
(command "_circle" "4797.164,914.7" "0.15")
(command "_circle" "4796.789,914.7" "0.15")
(command "_circle" "4796.414,914.7" "0.075")
(command "_circle" "4796.039,914.7" "0.075")
(command "_circle" "4795.664,914.7" "0.15")
(command "_circle" "4797.914,916.7" "0.075")
(command "_circle" "4797.539,916.7" "0.075")
(command "_circle" "4797.164,916.7" "0.075")
(command "_circle" "4796.789,916.7" "0.075")
(command "_circle" "4796.414,916.7" "0.15")
(command "_circle" "4796.039,916.7" "0.075")
(command "_circle" "4795.664,916.7" "0.15")
(command "_circle" "4797.914,918.7" "0.075")
(command "_circle" "4797.539,918.7" "0.15")
(command "_circle" "4797.164,918.7" "0.075")
(command "_circle" "4796.789,918.7" "0.075")
(command "_circle" "4796.414,918.7" "0.15")
(command "_circle" "4796.039,918.7" "0.075")
(command "_circle" "4795.664,918.7" "0.15")
(command "_circle" "4797.914,920.7" "0.075")
(command "_circle" "4797.539,920.7" "0.075")
(command "_circle" "4797.164,920.7" "0.15")
(command "_circle" "4796.789,920.7" "0.075")
(command "_circle" "4796.414,920.7" "0.15")
(command "_circle" "4796.039,920.7" "0.075")
(command "_circle" "4795.664,920.7" "0.15")
(command "_circle" "4797.914,922.7" "0.075")
(command "_circle" "4797.539,922.7" "0.15")
(command "_circle" "4797.164,922.7" "0.15")
(command "_circle" "4796.789,922.7" "0.075")
(command "_circle" "4796.414,922.7" "0.15")
(command "_circle" "4796.039,922.7" "0.075")
(command "_circle" "4795.664,922.7" "0.15")
(command "_circle" "4797.914,924.7" "0.075")
(command "_circle" "4797.539,924.7" "0.075")
(command "_circle" "4797.164,924.7" "0.075")
(command "_circle" "4796.789,924.7" "0.15")
(command "_circle" "4796.414,924.7" "0.15")
(command "_circle" "4796.039,924.7" "0.075")
(command "_circle" "4795.664,924.7" "0.15")
(command "_circle" "4797.914,926.7" "0.075")
(command "_circle" "4797.539,926.7" "0.15")
(command "_circle" "4797.164,926.7" "0.075")
(command "_circle" "4796.789,926.7" "0.15")
(command "_circle" "4796.414,926.7" "0.15")
(command "_circle" "4796.039,926.7" "0.075")
(command "_circle" "4795.664,926.7" "0.15")
(command "_circle" "4797.914,928.7" "0.075")
(command "_circle" "4797.539,928.7" "0.075")
(command "_circle" "4797.164,928.7" "0.15")
(command "_circle" "4796.789,928.7" "0.15")
(command "_circle" "4796.414,928.7" "0.15")
(command "_circle" "4796.039,928.7" "0.075")
(command "_circle" "4795.664,928.7" "0.15")
(command "_circle" "4797.914,930.7" "0.075")
(command "_circle" "4797.539,930.7" "0.15")
(command "_circle" "4797.164,930.7" "0.15")
(command "_circle" "4796.789,930.7" "0.15")
(command "_circle" "4796.414,930.7" "0.15")
(command "_circle" "4796.039,930.7" "0.075")
(command "_circle" "4795.664,930.7" "0.15")
(command "_circle" "4797.914,932.7" "0.075")
(command "_circle" "4797.539,932.7" "0.075")
(command "_circle" "4797.164,932.7" "0.075")
(command "_circle" "4796.789,932.7" "0.075")
(command "_circle" "4796.414,932.7" "0.075")
(command "_circle" "4796.039,932.7" "0.15")
(command "_circle" "4795.664,932.7" "0.15")
(command "_circle" "4797.914,934.7" "0.075")
(command "_circle" "4797.539,934.7" "0.15")
(command "_circle" "4797.164,934.7" "0.075")
(command "_circle" "4796.789,934.7" "0.075")
(command "_circle" "4796.414,934.7" "0.075")
(command "_circle" "4796.039,934.7" "0.15")
(command "_circle" "4795.664,934.7" "0.15")
(command "_circle" "4797.914,936.7" "0.075")
(command "_circle" "4797.539,936.7" "0.075")
(command "_circle" "4797.164,936.7" "0.15")
(command "_circle" "4796.789,936.7" "0.075")
(command "_circle" "4796.414,936.7" "0.075")
(command "_circle" "4796.039,936.7" "0.15")
(command "_circle" "4795.664,936.7" "0.15")
(command "_circle" "4797.914,938.7" "0.075")
(command "_circle" "4797.539,938.7" "0.15")
(command "_circle" "4797.164,938.7" "0.15")
(command "_circle" "4796.789,938.7" "0.075")
(command "_circle" "4796.414,938.7" "0.075")
(command "_circle" "4796.039,938.7" "0.15")
(command "_circle" "4795.664,938.7" "0.15")
(command "_circle" "4797.914,940.7" "0.075")
(command "_circle" "4797.539,940.7" "0.075")
(command "_circle" "4797.164,940.7" "0.075")
(command "_circle" "4796.789,940.7" "0.15")
(command "_circle" "4796.414,940.7" "0.075")
(command "_circle" "4796.039,940.7" "0.15")
(command "_circle" "4795.664,940.7" "0.15")
(command "_circle" "4797.914,942.7" "0.075")
(command "_circle" "4797.539,942.7" "0.15")
(command "_circle" "4797.164,942.7" "0.075")
(command "_circle" "4796.789,942.7" "0.15")
(command "_circle" "4796.414,942.7" "0.075")
(command "_circle" "4796.039,942.7" "0.15")
(command "_circle" "4795.664,942.7" "0.15")
(command "_circle" "4797.914,944.7" "0.075")
(command "_circle" "4797.539,944.7" "0.075")
(command "_circle" "4797.164,944.7" "0.15")
(command "_circle" "4796.789,944.7" "0.15")
(command "_circle" "4796.414,944.7" "0.075")
(command "_circle" "4796.039,944.7" "0.15")
(command "_circle" "4795.664,944.7" "0.15")
(command "_circle" "4797.914,946.7" "0.075")
(command "_circle" "4797.539,946.7" "0.15")
(command "_circle" "4797.164,946.7" "0.15")
(command "_circle" "4796.789,946.7" "0.15")
(command "_circle" "4796.414,946.7" "0.075")
(command "_circle" "4796.039,946.7" "0.15")
(command "_circle" "4795.664,946.7" "0.15")
(command "_circle" "4797.914,948.7" "0.075")
(command "_circle" "4797.539,948.7" "0.075")
(command "_circle" "4797.164,948.7" "0.075")
(command "_circle" "4796.789,948.7" "0.075")
(command "_circle" "4796.414,948.7" "0.15")
(command "_circle" "4796.039,948.7" "0.15")
(command "_circle" "4795.664,948.7" "0.15")
(command "_circle" "4797.914,950.7" "0.075")
(command "_circle" "4797.539,950.7" "0.15")
(command "_circle" "4797.164,950.7" "0.075")
(command "_circle" "4796.789,950.7" "0.075")
(command "_circle" "4796.414,950.7" "0.15")
(command "_circle" "4796.039,950.7" "0.15")
(command "_circle" "4795.664,950.7" "0.15")
(command "_circle" "4797.914,952.7" "0.075")
(command "_circle" "4797.539,952.7" "0.075")
(command "_circle" "4797.164,952.7" "0.15")
(command "_circle" "4796.789,952.7" "0.075")
(command "_circle" "4796.414,952.7" "0.15")
(command "_circle" "4796.039,952.7" "0.15")
(command "_circle" "4795.664,952.7" "0.15")
(command "_circle" "4797.914,954.7" "0.075")
(command "_circle" "4797.539,954.7" "0.15")
(command "_circle" "4797.164,954.7" "0.15")
(command "_circle" "4796.789,954.7" "0.075")
(command "_circle" "4796.414,954.7" "0.15")
(command "_circle" "4796.039,954.7" "0.15")
(command "_circle" "4795.664,954.7" "0.15")
(command "_circle" "4797.914,956.7" "0.075")
(command "_circle" "4797.539,956.7" "0.075")
(command "_circle" "4797.164,956.7" "0.075")
(command "_circle" "4796.789,956.7" "0.15")
(command "_circle" "4796.414,956.7" "0.15")
(command "_circle" "4796.039,956.7" "0.15")
(command "_circle" "4795.664,956.7" "0.15")
(command "_circle" "4797.914,958.7" "0.075")
(command "_circle" "4797.539,958.7" "0.15")
(command "_circle" "4797.164,958.7" "0.075")
(command "_circle" "4796.789,958.7" "0.15")
(command "_circle" "4796.414,958.7" "0.15")
(command "_circle" "4796.039,958.7" "0.15")
(command "_circle" "4795.664,958.7" "0.15")
(command "_circle" "4797.914,960.7" "0.075")
(command "_circle" "4797.539,960.7" "0.075")
(command "_circle" "4797.164,960.7" "0.15")
(command "_circle" "4796.789,960.7" "0.15")
(command "_circle" "4796.414,960.7" "0.15")
(command "_circle" "4796.039,960.7" "0.15")
(command "_circle" "4795.664,960.7" "0.15")
(command "_circle" "4797.914,962.7" "0.075")
(command "_circle" "4797.539,962.7" "0.15")
(command "_circle" "4797.164,962.7" "0.15")
(command "_circle" "4796.789,962.7" "0.15")
(command "_circle" "4796.414,962.7" "0.15")
(command "_circle" "4796.039,962.7" "0.15")
(command "_circle" "4795.664,962.7" "0.15")
(command "_layer" "set" "nitride" "")
(command "_layer" "set" "text" "")
(command-s "_text" "4786.864,963.3" "2" "-90" "a = 370 nm" )
(sssetfirst nil (ssget "_L"))
(if (not (numberp (vl-string-search "Mac" (getvar "platform")))) (c:txtexp))
(command "_layer" "set" "nitride" "")
(command "_layer" "set" "text" "")
(command-s "_text" "4783.864,963.3" "2" "-90" "gap = 270 nm" )
(sssetfirst nil (ssget "_L"))
(if (not (numberp (vl-string-search "Mac" (getvar "platform")))) (c:txtexp))
(command "_layer" "set" "nitride" "")
(command "_layer" "set" "text" "")
(command-s "_text" "4780.864,963.3" "2" "-90" "amplitude = 135 nm" )
(sssetfirst nil (ssget "_L"))
(if (not (numberp (vl-string-search "Mac" (getvar "platform")))) (c:txtexp))
(command "_layer" "set" "nitride" "")
(command "_layer" "set" "text" "")
(command-s "_text" "4777.864,963.3" "2" "-90" "start width = 280 nm" )
(sssetfirst nil (ssget "_L"))
(if (not (numberp (vl-string-search "Mac" (getvar "platform")))) (c:txtexp))
(command "_layer" "set" "nitride" "")
(command "_layer" "set" "text" "")
(command-s "_text" "4774.864,963.3" "2" "-90" "width = 298 nm" )
(sssetfirst nil (ssget "_L"))
(if (not (numberp (vl-string-search "Mac" (getvar "platform")))) (c:txtexp))
(command "_layer" "set" "nitride" "")
(command "_layer" "set" "text" "")
(command-s "_text" "4771.864,963.3" "2" "-90" "taper: 15" )
(sssetfirst nil (ssget "_L"))
(if (not (numberp (vl-string-search "Mac" (getvar "platform")))) (c:txtexp))
(command "_layer" "set" "nitride" "")
(command "_layer" "set" "text" "")
(command-s "_text" "4768.864,963.3" "2" "-90" "nominal: 150" )
(sssetfirst nil (ssget "_L"))
(if (not (numberp (vl-string-search "Mac" (getvar "platform")))) (c:txtexp))
(command "_layer" "set" "nitride" "")
(command "_layer" "set" "indicators" "")
(setq coords (list 
(list 4720.415 940) 
(list 4720.415 920) 
(list 4700.415 900) 
(list 4720.415 880) 
(list 4720.415 860) 
(list 4720.415 900) 
(list 4720.415 887.0711) 
(list 4707.4861 900) 
(list 4720.415 912.9289) 
(list 4720.415 900)))
(apply 'command (append '("pline") coords '("c")))
(command "._fillet" "radius" "1" "._fillet" "P" (entlast))
(setq coords (list 
(list 4879.585 940) 
(list 4879.585 920) 
(list 4899.585 900) 
(list 4879.585 880) 
(list 4879.585 860) 
(list 4879.585 900) 
(list 4879.585 887.0711) 
(list 4892.5139 900) 
(list 4879.585 912.9289) 
(list 4879.585 900)))
(apply 'command (append '("pline") coords '("c")))
(command "._fillet" "radius" "1" "._fillet" "P" (entlast))
(command "_layer" "set" "holes" "")
(command "_circle" "4718.0629,914.1124" "0.5")
(command "_circle" "4715.7109,911.7603" "0.5")
(command "_circle" "4713.3588,909.4083" "0.5")
(command "_circle" "4711.0067,907.0562" "0.5")
(command "_circle" "4708.6547,904.7041" "0.5")
(command "_circle" "4706.3026,902.3521" "0.5")
(command "_circle" "4703.9505,900" "0.5")
(command "_circle" "4706.3026,897.6479" "0.5")
(command "_circle" "4708.6547,895.2959" "0.5")
(command "_circle" "4711.0067,892.9438" "0.5")
(command "_circle" "4713.3588,890.5917" "0.5")
(command "_circle" "4715.7109,888.2397" "0.5")
(command "_circle" "4718.0629,885.8876" "0.5")
(command "_circle" "4881.9371,914.1124" "0.5")
(command "_circle" "4884.2891,911.7603" "0.5")
(command "_circle" "4886.6412,909.4083" "0.5")
(command "_circle" "4888.9933,907.0562" "0.5")
(command "_circle" "4891.3453,904.7041" "0.5")
(command "_circle" "4893.6974,902.3521" "0.5")
(command "_circle" "4896.0495,900" "0.5")
(command "_circle" "4893.6974,897.6479" "0.5")
(command "_circle" "4891.3453,895.2959" "0.5")
(command "_circle" "4888.9933,892.9438" "0.5")
(command "_circle" "4886.6412,890.5917" "0.5")
(command "_circle" "4884.2891,888.2397" "0.5")
(command "_circle" "4881.9371,885.8876" "0.5")
(command "_layer" "set" "nitride" "")
(command "_block" "blkcoupler15" "4800,900" coupler15 "")
(command "_insert" "blkcoupler15" "4800,900" "1" "1" "0")
(command "_insert" "blkcoupler15" "4800,900" "1" "1" "180")
(command "_block" "blksinglenanobeam15" "4800,900" singlenanobeam15 "")
(command "_insert" "blksinglenanobeam15" "4800,900" "1" "1" "0")
(command "_insert" "blksinglenanobeam15" "4800,900" "1" "1" "180")
(command "_block" "blkanglednodearray15" "4800,900" anglednodearray15 "")
(command "_insert" "blkanglednodearray15" "4800,900" "1" "1" "0")
(command "_insert" "blkanglednodearray15" "4800,900" "1" "1" "180")
(command "_block" "blkcooledsinglenanobeam15" "4800,900" cooledsinglenanobeam15 "")
(command "_insert" "blkcooledsinglenanobeam15" "4800,900" "1" "1" "0")
(command "_insert" "blkcooledsinglenanobeam15" "4800,900" "1" "1" "180")
(command "_block" "blkyjunction15" "4800,900" yjunction15 "")
(command "_insert" "blkyjunction15" "4800,900" "1" "1" "0")
(command "_insert" "blkyjunction15" "4800,900" "1" "1" "180")
; DRAWING BULGING VEE GROOVE
(command "_layer" "set" "vgroove" "")
(setq coords (list 
(list 4725.415 -605) 
(list 4725.415 0) 
(list 4725.415 0) 
(list 4725.415 1800) 
(list 4725.415 1800) 
(list 4725.415 2405) 
(list 4874.585 2405) 
(list 4874.585 1800) 
(list 4874.585 1800) 
(list 4874.585 0) 
(list 4874.585 0) 
(list 4874.585 -605)))
(apply 'command (append '("pline") coords '("c")))
(command "._fillet" "radius" "0" "._fillet" "P" (entlast))
(command "_layer" "set" "window" "")
(command "_rectangle" "4725.415,-1935" "4874.585,-600")
(command "_rectangle" "4725.415,2400" "4874.585,5300")
(command "_layer" "set" "grid" "")
(command "_rectangle" "4726.415,-1934" "4749.9433,-1909.2133")
(command "_array" "last" "" "R" "75" "3" "25.7867" "24.5283")
(command "_rectangle" "4801,-1934" "4824.5283,-1909.2133")
(command "_array" "last" "" "R" "75" "3" "25.7867" "24.5283")
(command "_rectangle" "4726.415,1" "4749.9433,25.7")
(command "_array" "last" "" "R" "70" "3" "25.7" "24.5283")
(command "_rectangle" "4801,1" "4824.5283,25.7")
(command "_array" "last" "" "R" "70" "3" "25.7" "24.5283")
(command "_rectangle" "4726.415,1801" "4749.9433,1825.9185")
(command "_array" "last" "" "R" "135" "3" "25.9185" "24.5283")
(command "_rectangle" "4801,1801" "4824.5283,1825.9185")
(command "_array" "last" "" "R" "135" "3" "25.9185" "24.5283")
(command "_layer" "set" "vgrooveFDA" "")
(command "_rectangle" "4874.585,-2233" "4725.415,-1933")
(command "_layer" "set" "nitride" "")
(command "_layer" "set" "holes" "")
(command "_circle" "4877.085,331.5" "0.5")
(command "_array" "last" "" "R" "379" "1" "3" "2.5")
(command "_circle" "4722.915,331.5" "0.5")
(command "_array" "last" "" "R" "379" "1" "3" "-2.5")
(command "_layer" "set" "nitride" "")
(command "_layer" "set" "window" "")
(command "_layer" "set" "window" "")
(command "_rectangle" "4879.585,0" "5040.415,1800")
(command "._fillet" "radius" "20" "._fillet" "P" (entlast))
(command "_layer" "set" "grid" "")
(command "_rectangle" "4880.585,1" "4902.4179,25.7")
(command "_array" "last" "" "R" "70" "7" "25.7" "22.8329")
(command "_layer" "set" "nitride" "")
; DRAWING REGION LAYER
(command "_layer" "set" "regionLayer15" "")
(command "_rectangle" "4720,-460" "4880,2260")
(command "_layer" "set" "nitride" "")
(setq coupler15 nil)
(setq singlenanobeam15 nil)
(setq anglednodearray15 nil)
(setq cooledsinglenanobeam15 nil)
(setq yjunction15 nil)
; DEVICE #16
(command "_layer" "set" "window" "")
(command "_circle" "5032.915,-415" "5")
(command "_circle" "5032.915,-402.5" "5")
(command "_circle" "5032.915,-390" "5")
(command "_circle" "5032.915,-377.5" "5")
(command "_circle" "5020.415,-415" "5")
(command "_circle" "5020.415,-402.5" "5")
(command "_circle" "5020.415,-390" "5")
(command "_circle" "5020.415,-377.5" "5")
(command "_circle" "5007.915,-415" "5")
(command "_circle" "5007.915,-402.5" "5")
(command "_circle" "5007.915,-390" "5")
(command "_circle" "5007.915,-377.5" "5")
(command "_circle" "4995.415,-415" "5")
(command "_circle" "4995.415,-402.5" "5")
(command "_circle" "4995.415,-390" "5")
(command "_circle" "4995.415,-377.5" "5")
(command "_layer" "set" "nitride" "")
(setq currobj nil)
(setq currobj (ssadd))
; DRAWING COUPLER
(setq coords (list 
(list 5120.0645 -415) 
(list 5120.0645 -413) 
(list 5193.585 -413) 
(list 5193.585 -413) 
(list 5193.9677 -413.0761) 
(list 5194.2921 -413.2929) 
(list 5194.5089 -413.6173) 
(list 5194.585 -414) 
(list 5194.585 -411.8) 
(list 5194.585 -411.8) 
(list 5194.5089 -412.1827) 
(list 5194.2921 -412.5071) 
(list 5193.9677 -412.7239) 
(list 5193.585 -412.8) 
(list 5120.0645 -412.8) 
(list 5120.0645 -410.8) 
(list 5119.9355 -410.8) 
(list 5119.9355 -412.8) 
(list 5046.415 -412.8) 
(list 5046.0323 -412.7239) 
(list 5045.7079 -412.5071) 
(list 5045.4911 -412.1827) 
(list 5045.415 -411.8) 
(list 5045.415 -411.8) 
(list 5045.415 -414) 
(list 5045.4911 -413.6173) 
(list 5045.7079 -413.2929) 
(list 5046.0323 -413.0761) 
(list 5046.415 -413) 
(list 5046.415 -413) 
(list 5119.9355 -413) 
(list 5119.9355 -415)))
(apply 'command (append '("pline") coords '("c")))
(setq currobj (ssadd (entlast) currobj))
(command "._fillet" "radius" "0.3" "._fillet" "P" (entlast))
(command "_layer" "set" "holes" "")
(command "_circle" "5120,-412.9" "0.113")
(setq currobj (ssadd (entlast) currobj))
(command "_layer" "set" "nitride" "")
(command "_layer" "set" "text" "")
(command "_circle" "5119.2,-415" "0.075")
(command "_circle" "5119.2,-414.7" "0.075")
(command "_circle" "5119.2,-414.4" "0.075")
(command "_circle" "5118.9,-415" "0.075")
(command "_circle" "5118.9,-414.7" "0.075")
(command "_circle" "5118.9,-414.4" "0.075")
(command "_circle" "5118.6,-415" "0.075")
(command "_circle" "5118.6,-414.7" "0.075")
(command "_circle" "5118.6,-414.4" "0.075")
(command "_layer" "set" "nitride" "")
(command "_layer" "set" "prebias" "")
(command "_rectangle" "5045.415,-414" "5194.585,-411.8")
(setq currobj (ssadd (entlast) currobj))
(command "_rectangle" "5119.9355,-415" "5120.0645,-410.8")
(setq currobj (ssadd (entlast) currobj))
(command "_layer" "set" "nitride" "")
(setq coupler16 currobj)
(setq currobj nil)
(setq currobj (ssadd))
; DRAWING SINGLE NANOBEAM
(setq coords (list 
(list 5120.0645 -410.8) 
(list 5120.0645 -409.1417) 
(list 5120.0645 -407.4833) 
(list 5120.0645 -405.825) 
(list 5120.0645 -404.1667) 
(list 5120.0645 -402.5083) 
(list 5120.0645 -400.85) 
(list 5120.0645 -399.1917) 
(list 5120.0645 -397.5333) 
(list 5120.0646 -395.875) 
(list 5120.0646 -394.2167) 
(list 5120.0646 -392.5583) 
(list 5120.0646 -390.9) 
(list 5120.0647 -389.2417) 
(list 5120.0647 -387.5833) 
(list 5120.0647 -385.925) 
(list 5120.0648 -384.2667) 
(list 5120.0648 -382.6083) 
(list 5120.0649 -380.95) 
(list 5120.065 -379.2917) 
(list 5120.0651 -377.6333) 
(list 5120.0651 -375.975) 
(list 5120.0652 -374.3167) 
(list 5120.0653 -372.6583) 
(list 5120.0655 -371) 
(list 5120.0656 -369.3417) 
(list 5120.0657 -367.6833) 
(list 5120.0659 -366.025) 
(list 5120.066 -364.3667) 
(list 5120.0662 -362.7083) 
(list 5120.0664 -361.05) 
(list 5120.0666 -359.3917) 
(list 5120.0668 -357.7333) 
(list 5120.067 -356.075) 
(list 5120.0672 -354.4167) 
(list 5120.0675 -352.7583) 
(list 5120.0678 -351.1) 
(list 5120.068 -349.4417) 
(list 5120.0683 -347.7833) 
(list 5120.0686 -346.125) 
(list 5120.069 -344.4667) 
(list 5120.0693 -342.8083) 
(list 5120.0697 -341.15) 
(list 5120.07 -339.4917) 
(list 5120.0704 -337.8333) 
(list 5120.0709 -336.175) 
(list 5120.0713 -334.5167) 
(list 5120.0717 -332.8583) 
(list 5120.0722 -331.2) 
(list 5120.0727 -329.5417) 
(list 5120.0732 -327.8833) 
(list 5120.0737 -326.225) 
(list 5120.0743 -324.5667) 
(list 5120.0749 -322.9083) 
(list 5120.0755 -321.25) 
(list 5120.0761 -319.5917) 
(list 5120.0767 -317.9333) 
(list 5120.0774 -316.275) 
(list 5120.0781 -314.6167) 
(list 5120.0788 -312.9583) 
(list 5120.0796 -311.3) 
(list 5120.0803 -309.6417) 
(list 5120.0811 -307.9833) 
(list 5120.0819 -306.325) 
(list 5120.0828 -304.6667) 
(list 5120.0837 -303.0083) 
(list 5120.0845 -301.35) 
(list 5120.0855 -299.6917) 
(list 5120.0864 -298.0333) 
(list 5120.0874 -296.375) 
(list 5120.0884 -294.7167) 
(list 5120.0895 -293.0583) 
(list 5120.0905 -291.4) 
(list 5120.0916 -289.7417) 
(list 5120.0928 -288.0833) 
(list 5120.0939 -286.425) 
(list 5120.0951 -284.7667) 
(list 5120.0963 -283.1083) 
(list 5120.0976 -281.45) 
(list 5120.0989 -279.7917) 
(list 5120.1002 -278.1333) 
(list 5120.1016 -276.475) 
(list 5120.1029 -274.8167) 
(list 5120.1044 -273.1583) 
(list 5120.1058 -271.5) 
(list 5120.1073 -269.8417) 
(list 5120.1089 -268.1833) 
(list 5120.1104 -266.525) 
(list 5120.112 -264.8667) 
(list 5120.1137 -263.2083) 
(list 5120.1153 -261.55) 
(list 5120.117 -259.8917) 
(list 5120.1188 -258.2333) 
(list 5120.1206 -256.575) 
(list 5120.1224 -254.9167) 
(list 5120.1243 -253.2583) 
(list 5120.1262 -251.6) 
(list 5120.1281 -249.9417) 
(list 5120.1301 -248.2833) 
(list 5120.1322 -246.625) 
(list 5120.1342 -244.9667) 
(list 5120.1363 -243.3083) 
(list 5120.1385 -241.65) 
(list 5120.1407 -239.9917) 
(list 5120.1429 -238.3333) 
(list 5120.1452 -236.675) 
(list 5120.1476 -235.0167) 
(list 5120.1499 -233.3583) 
(list 5120.1523 -231.7) 
(list 5120.1548 -230.0417) 
(list 5120.1573 -228.3833) 
(list 5120.1599 -226.725) 
(list 5120.1625 -225.0667) 
(list 5120.1651 -223.4083) 
(list 5120.1678 -221.75) 
(list 5120.1706 -220.0917) 
(list 5120.1733 -218.4333) 
(list 5120.1762 -216.775) 
(list 5120.1791 -215.1167) 
(list 5120.182 -213.4583) 
(list 5120.185 -211.8) 
(list 5119.815 -211.8) 
(list 5119.818 -213.4583) 
(list 5119.8209 -215.1167) 
(list 5119.8238 -216.775) 
(list 5119.8267 -218.4333) 
(list 5119.8294 -220.0917) 
(list 5119.8322 -221.75) 
(list 5119.8349 -223.4083) 
(list 5119.8375 -225.0667) 
(list 5119.8401 -226.725) 
(list 5119.8427 -228.3833) 
(list 5119.8452 -230.0417) 
(list 5119.8477 -231.7) 
(list 5119.8501 -233.3583) 
(list 5119.8524 -235.0167) 
(list 5119.8548 -236.675) 
(list 5119.8571 -238.3333) 
(list 5119.8593 -239.9917) 
(list 5119.8615 -241.65) 
(list 5119.8637 -243.3083) 
(list 5119.8658 -244.9667) 
(list 5119.8678 -246.625) 
(list 5119.8699 -248.2833) 
(list 5119.8719 -249.9417) 
(list 5119.8738 -251.6) 
(list 5119.8757 -253.2583) 
(list 5119.8776 -254.9167) 
(list 5119.8794 -256.575) 
(list 5119.8812 -258.2333) 
(list 5119.883 -259.8917) 
(list 5119.8847 -261.55) 
(list 5119.8863 -263.2083) 
(list 5119.888 -264.8667) 
(list 5119.8896 -266.525) 
(list 5119.8911 -268.1833) 
(list 5119.8927 -269.8417) 
(list 5119.8942 -271.5) 
(list 5119.8956 -273.1583) 
(list 5119.8971 -274.8167) 
(list 5119.8984 -276.475) 
(list 5119.8998 -278.1333) 
(list 5119.9011 -279.7917) 
(list 5119.9024 -281.45) 
(list 5119.9037 -283.1083) 
(list 5119.9049 -284.7667) 
(list 5119.9061 -286.425) 
(list 5119.9072 -288.0833) 
(list 5119.9084 -289.7417) 
(list 5119.9095 -291.4) 
(list 5119.9105 -293.0583) 
(list 5119.9116 -294.7167) 
(list 5119.9126 -296.375) 
(list 5119.9136 -298.0333) 
(list 5119.9145 -299.6917) 
(list 5119.9155 -301.35) 
(list 5119.9163 -303.0083) 
(list 5119.9172 -304.6667) 
(list 5119.9181 -306.325) 
(list 5119.9189 -307.9833) 
(list 5119.9197 -309.6417) 
(list 5119.9204 -311.3) 
(list 5119.9212 -312.9583) 
(list 5119.9219 -314.6167) 
(list 5119.9226 -316.275) 
(list 5119.9233 -317.9333) 
(list 5119.9239 -319.5917) 
(list 5119.9245 -321.25) 
(list 5119.9251 -322.9083) 
(list 5119.9257 -324.5667) 
(list 5119.9263 -326.225) 
(list 5119.9268 -327.8833) 
(list 5119.9273 -329.5417) 
(list 5119.9278 -331.2) 
(list 5119.9283 -332.8583) 
(list 5119.9287 -334.5167) 
(list 5119.9291 -336.175) 
(list 5119.9296 -337.8333) 
(list 5119.93 -339.4917) 
(list 5119.9303 -341.15) 
(list 5119.9307 -342.8083) 
(list 5119.931 -344.4667) 
(list 5119.9314 -346.125) 
(list 5119.9317 -347.7833) 
(list 5119.932 -349.4417) 
(list 5119.9322 -351.1) 
(list 5119.9325 -352.7583) 
(list 5119.9328 -354.4167) 
(list 5119.933 -356.075) 
(list 5119.9332 -357.7333) 
(list 5119.9334 -359.3917) 
(list 5119.9336 -361.05) 
(list 5119.9338 -362.7083) 
(list 5119.934 -364.3667) 
(list 5119.9341 -366.025) 
(list 5119.9343 -367.6833) 
(list 5119.9344 -369.3417) 
(list 5119.9345 -371) 
(list 5119.9347 -372.6583) 
(list 5119.9348 -374.3167) 
(list 5119.9349 -375.975) 
(list 5119.9349 -377.6333) 
(list 5119.935 -379.2917) 
(list 5119.9351 -380.95) 
(list 5119.9352 -382.6083) 
(list 5119.9352 -384.2667) 
(list 5119.9353 -385.925) 
(list 5119.9353 -387.5833) 
(list 5119.9353 -389.2417) 
(list 5119.9354 -390.9) 
(list 5119.9354 -392.5583) 
(list 5119.9354 -394.2167) 
(list 5119.9354 -395.875) 
(list 5119.9355 -397.5333) 
(list 5119.9355 -399.1917) 
(list 5119.9355 -400.85) 
(list 5119.9355 -402.5083) 
(list 5119.9355 -404.1667) 
(list 5119.9355 -405.825) 
(list 5119.9355 -407.4833) 
(list 5119.9355 -409.1417) 
(list 5119.9355 -410.8)))
(apply 'command (append '("pline") coords '("c")))
(setq currobj (ssadd (entlast) currobj))
(command "_layer" "set" "prebias" "")
(command "_rectangle" "5119.815,-410.8" "5120.185,-211.8")
(setq currobj (ssadd (entlast) currobj))
(command "_layer" "set" "nitride" "")
(setq singlenanobeam16 currobj)
(setq currobj nil)
(setq currobj (ssadd))
; DRAWING NODE ARRAY
(setq coords (list 
(list 5120.185 -211.8) 
(list 5120.5625 -201.8) 
(list 5120.5625 -201.8) 
(list 5120.5625 -200.8) 
(list 5194.585 -212.6864) 
(list 5194.585 -207.7434) 
(list 5120.5625 -197.357) 
(list 5120.5625 -196.357) 
(list 5120.5625 -196.357) 
(list 5120.2625 -186.357) 
(list 5119.7375 -186.357) 
(list 5119.4375 -196.357) 
(list 5119.4375 -196.357) 
(list 5119.4375 -197.357) 
(list 5045.415 -207.7434) 
(list 5045.415 -212.6864) 
(list 5119.4375 -200.8) 
(list 5119.4375 -201.8) 
(list 5119.4375 -201.8) 
(list 5119.815 -211.8)))
(apply 'command (append '("pline") coords '("c")))
(setq currobj (ssadd (entlast) currobj))
(command "_layer" "set" "prebias" "")
(setq coords (list 
(list 5119.4375 -212.6864) 
(list 5119.4375 -200.8) 
(list 5045.415 -212.6864) 
(list 5045.415 -207.7434) 
(list 5119.4375 -197.357) 
(list 5119.4375 -186.357) 
(list 5120.5625 -186.357) 
(list 5120.5625 -197.357) 
(list 5194.585 -207.7434) 
(list 5194.585 -212.6864) 
(list 5120.5625 -200.8) 
(list 5120.5625 -212.6864)))
(apply 'command (append '("pline") coords '("c")))
(setq currobj (ssadd (entlast) currobj))
(command "_layer" "set" "nitride" "")
(command "_layer" "set" "fda1" "")
(setq coords (list 
(list 5120.5625 -200.657) 
(list 5194.585 -212.5434) 
(list 5194.585 -212.3664) 
(list 5120.5625 -200.58)))
(apply 'command (append '("pline") coords '("c")))
(setq currobj (ssadd (entlast) currobj))
(setq coords (list 
(list 5120.5625 -200.437) 
(list 5194.585 -212.2234) 
(list 5194.585 -212.0464) 
(list 5120.5625 -200.36)))
(apply 'command (append '("pline") coords '("c")))
(setq currobj (ssadd (entlast) currobj))
(setq coords (list 
(list 5120.5625 -200.217) 
(list 5194.585 -211.9034) 
(list 5194.585 -211.7264) 
(list 5120.5625 -200.14)))
(apply 'command (append '("pline") coords '("c")))
(setq currobj (ssadd (entlast) currobj))
(setq coords (list 
(list 5120.5625 -199.997) 
(list 5194.585 -211.5834) 
(list 5194.585 -211.4064) 
(list 5120.5625 -199.92)))
(apply 'command (append '("pline") coords '("c")))
(setq currobj (ssadd (entlast) currobj))
(setq coords (list 
(list 5120.5625 -199.777) 
(list 5194.585 -211.2634) 
(list 5194.585 -211.0864) 
(list 5120.5625 -199.7)))
(apply 'command (append '("pline") coords '("c")))
(setq currobj (ssadd (entlast) currobj))
(setq coords (list 
(list 5120.5625 -199.557) 
(list 5194.585 -210.9434) 
(list 5194.585 -210.7664) 
(list 5120.5625 -199.48)))
(apply 'command (append '("pline") coords '("c")))
(setq currobj (ssadd (entlast) currobj))
(setq coords (list 
(list 5120.5625 -199.337) 
(list 5194.585 -210.6234) 
(list 5194.585 -210.4464) 
(list 5120.5625 -199.26)))
(apply 'command (append '("pline") coords '("c")))
(setq currobj (ssadd (entlast) currobj))
(setq coords (list 
(list 5120.5625 -199.117) 
(list 5194.585 -210.3034) 
(list 5194.585 -210.1264) 
(list 5120.5625 -199.04)))
(apply 'command (append '("pline") coords '("c")))
(setq currobj (ssadd (entlast) currobj))
(setq coords (list 
(list 5120.5625 -198.897) 
(list 5194.585 -209.9834) 
(list 5194.585 -209.8064) 
(list 5120.5625 -198.82)))
(apply 'command (append '("pline") coords '("c")))
(setq currobj (ssadd (entlast) currobj))
(setq coords (list 
(list 5120.5625 -198.677) 
(list 5194.585 -209.6634) 
(list 5194.585 -209.4864) 
(list 5120.5625 -198.6)))
(apply 'command (append '("pline") coords '("c")))
(setq currobj (ssadd (entlast) currobj))
(setq coords (list 
(list 5120.5625 -198.457) 
(list 5194.585 -209.3434) 
(list 5194.585 -209.1664) 
(list 5120.5625 -198.38)))
(apply 'command (append '("pline") coords '("c")))
(setq currobj (ssadd (entlast) currobj))
(setq coords (list 
(list 5120.5625 -198.237) 
(list 5194.585 -209.0234) 
(list 5194.585 -208.8464) 
(list 5120.5625 -198.16)))
(apply 'command (append '("pline") coords '("c")))
(setq currobj (ssadd (entlast) currobj))
(setq coords (list 
(list 5120.5625 -198.017) 
(list 5194.585 -208.7034) 
(list 5194.585 -208.5264) 
(list 5120.5625 -197.94)))
(apply 'command (append '("pline") coords '("c")))
(setq currobj (ssadd (entlast) currobj))
(setq coords (list 
(list 5120.5625 -197.797) 
(list 5194.585 -208.3834) 
(list 5194.585 -208.2064) 
(list 5120.5625 -197.72)))
(apply 'command (append '("pline") coords '("c")))
(setq currobj (ssadd (entlast) currobj))
(setq coords (list 
(list 5120.5625 -197.577) 
(list 5194.585 -208.0634) 
(list 5194.585 -207.8864) 
(list 5120.5625 -197.5)))
(apply 'command (append '("pline") coords '("c")))
(setq currobj (ssadd (entlast) currobj))
(setq coords (list 
(list 5119.4375 -197.5) 
(list 5045.415 -207.8864) 
(list 5045.415 -208.0634) 
(list 5119.4375 -197.577)))
(apply 'command (append '("pline") coords '("c")))
(setq currobj (ssadd (entlast) currobj))
(setq coords (list 
(list 5119.4375 -197.72) 
(list 5045.415 -208.2064) 
(list 5045.415 -208.3834) 
(list 5119.4375 -197.797)))
(apply 'command (append '("pline") coords '("c")))
(setq currobj (ssadd (entlast) currobj))
(setq coords (list 
(list 5119.4375 -197.94) 
(list 5045.415 -208.5264) 
(list 5045.415 -208.7034) 
(list 5119.4375 -198.017)))
(apply 'command (append '("pline") coords '("c")))
(setq currobj (ssadd (entlast) currobj))
(setq coords (list 
(list 5119.4375 -198.16) 
(list 5045.415 -208.8464) 
(list 5045.415 -209.0234) 
(list 5119.4375 -198.237)))
(apply 'command (append '("pline") coords '("c")))
(setq currobj (ssadd (entlast) currobj))
(setq coords (list 
(list 5119.4375 -198.38) 
(list 5045.415 -209.1664) 
(list 5045.415 -209.3434) 
(list 5119.4375 -198.457)))
(apply 'command (append '("pline") coords '("c")))
(setq currobj (ssadd (entlast) currobj))
(setq coords (list 
(list 5119.4375 -198.6) 
(list 5045.415 -209.4864) 
(list 5045.415 -209.6634) 
(list 5119.4375 -198.677)))
(apply 'command (append '("pline") coords '("c")))
(setq currobj (ssadd (entlast) currobj))
(setq coords (list 
(list 5119.4375 -198.82) 
(list 5045.415 -209.8064) 
(list 5045.415 -209.9834) 
(list 5119.4375 -198.897)))
(apply 'command (append '("pline") coords '("c")))
(setq currobj (ssadd (entlast) currobj))
(setq coords (list 
(list 5119.4375 -199.04) 
(list 5045.415 -210.1264) 
(list 5045.415 -210.3034) 
(list 5119.4375 -199.117)))
(apply 'command (append '("pline") coords '("c")))
(setq currobj (ssadd (entlast) currobj))
(setq coords (list 
(list 5119.4375 -199.26) 
(list 5045.415 -210.4464) 
(list 5045.415 -210.6234) 
(list 5119.4375 -199.337)))
(apply 'command (append '("pline") coords '("c")))
(setq currobj (ssadd (entlast) currobj))
(setq coords (list 
(list 5119.4375 -199.48) 
(list 5045.415 -210.7664) 
(list 5045.415 -210.9434) 
(list 5119.4375 -199.557)))
(apply 'command (append '("pline") coords '("c")))
(setq currobj (ssadd (entlast) currobj))
(setq coords (list 
(list 5119.4375 -199.7) 
(list 5045.415 -211.0864) 
(list 5045.415 -211.2634) 
(list 5119.4375 -199.777)))
(apply 'command (append '("pline") coords '("c")))
(setq currobj (ssadd (entlast) currobj))
(setq coords (list 
(list 5119.4375 -199.92) 
(list 5045.415 -211.4064) 
(list 5045.415 -211.5834) 
(list 5119.4375 -199.997)))
(apply 'command (append '("pline") coords '("c")))
(setq currobj (ssadd (entlast) currobj))
(setq coords (list 
(list 5119.4375 -200.14) 
(list 5045.415 -211.7264) 
(list 5045.415 -211.9034) 
(list 5119.4375 -200.217)))
(apply 'command (append '("pline") coords '("c")))
(setq currobj (ssadd (entlast) currobj))
(setq coords (list 
(list 5119.4375 -200.36) 
(list 5045.415 -212.0464) 
(list 5045.415 -212.2234) 
(list 5119.4375 -200.437)))
(apply 'command (append '("pline") coords '("c")))
(setq currobj (ssadd (entlast) currobj))
(setq coords (list 
(list 5119.4375 -200.58) 
(list 5045.415 -212.3664) 
(list 5045.415 -212.5434) 
(list 5119.4375 -200.657)))
(apply 'command (append '("pline") coords '("c")))
(setq currobj (ssadd (entlast) currobj))
(command "_layer" "set" "nitride" "")
(command "_layer" "set" "text" "")
(command "_circle" "5118.985,-211.8" "0.075")
(command "_circle" "5118.985,-211.5" "0.075")
(command "_circle" "5118.985,-211.2" "0.075")
(command "_circle" "5118.985,-210.9" "0.075")
(command "_circle" "5118.985,-210.6" "0.075")
(command "_circle" "5118.685,-211.8" "0.075")
(command "_circle" "5118.685,-211.5" "0.075")
(command "_circle" "5118.685,-211.2" "0.075")
(command "_circle" "5118.685,-210.9" "0.075")
(command "_circle" "5118.685,-210.6" "0.075")
(command "_circle" "5118.385,-211.8" "0.075")
(command "_circle" "5118.385,-211.5" "0.075")
(command "_circle" "5118.385,-211.2" "0.075")
(command "_circle" "5118.385,-210.9" "0.075")
(command "_circle" "5118.385,-210.6" "0.075")
(command "_circle" "5118.085,-211.8" "0.075")
(command "_circle" "5118.085,-211.5" "0.075")
(command "_circle" "5118.085,-211.2" "0.075")
(command "_circle" "5118.085,-210.9" "0.075")
(command "_circle" "5118.085,-210.6" "0.075")
(command "_circle" "5117.785,-211.8" "0.075")
(command "_circle" "5117.785,-211.5" "0.075")
(command "_circle" "5117.785,-211.2" "0.075")
(command "_circle" "5117.785,-210.9" "0.075")
(command "_circle" "5117.785,-210.6" "0.075")
(command "_layer" "set" "nitride" "")
(setq anglednodearray16 currobj)
(setq currobj nil)
(setq currobj (ssadd))
; DRAWING COOLED SINGLE NANOBEAM
(setq coords (list 
(list 5120.2625 -186.357) 
(list 5120.2625 -181.357) 
(list 5119.7375 -181.357) 
(list 5119.7375 -186.357)))
(apply 'command (append '("pline") coords '("c")))
(setq currobj (ssadd (entlast) currobj))
(command "_layer" "set" "prebias" "")
(command "_rectangle" "5119.7375,-186.357" "5120.2625,-181.357")
(setq currobj (ssadd (entlast) currobj))
(command "_layer" "set" "nitride" "")
(setq coords (list 
(list 5120.2625 -181.357) 
(list 5120.5625 -171.357) 
(list 5120.5625 -171.357) 
(list 5120.5625 -170.357) 
(list 5194.585 -171.107) 
(list 5194.585 -166.164) 
(list 5120.5625 -166.914) 
(list 5120.5625 -165.914) 
(list 5120.5625 -165.914) 
(list 5120.2625 -155.914) 
(list 5119.7375 -155.914) 
(list 5119.4375 -165.914) 
(list 5119.4375 -165.914) 
(list 5119.4375 -166.914) 
(list 5045.415 -166.164) 
(list 5045.415 -171.107) 
(list 5119.4375 -170.357) 
(list 5119.4375 -171.357) 
(list 5119.4375 -171.357) 
(list 5119.7375 -181.357)))
(apply 'command (append '("pline") coords '("c")))
(setq currobj (ssadd (entlast) currobj))
(command "_layer" "set" "prebias" "")
(setq coords (list 
(list 5119.4375 -181.357) 
(list 5119.4375 -170.357) 
(list 5045.415 -171.107) 
(list 5045.415 -166.164) 
(list 5119.4375 -166.914) 
(list 5119.4375 -155.914) 
(list 5120.5625 -155.914) 
(list 5120.5625 -166.914) 
(list 5194.585 -166.164) 
(list 5194.585 -171.107) 
(list 5120.5625 -170.357) 
(list 5120.5625 -181.357)))
(apply 'command (append '("pline") coords '("c")))
(setq currobj (ssadd (entlast) currobj))
(command "_layer" "set" "nitride" "")
(command "_layer" "set" "fda1" "")
(setq coords (list 
(list 5120.5625 -170.214) 
(list 5194.585 -170.964) 
(list 5194.585 -170.787) 
(list 5120.5625 -170.137)))
(apply 'command (append '("pline") coords '("c")))
(setq currobj (ssadd (entlast) currobj))
(setq coords (list 
(list 5120.5625 -169.994) 
(list 5194.585 -170.644) 
(list 5194.585 -170.467) 
(list 5120.5625 -169.917)))
(apply 'command (append '("pline") coords '("c")))
(setq currobj (ssadd (entlast) currobj))
(setq coords (list 
(list 5120.5625 -169.774) 
(list 5194.585 -170.324) 
(list 5194.585 -170.147) 
(list 5120.5625 -169.697)))
(apply 'command (append '("pline") coords '("c")))
(setq currobj (ssadd (entlast) currobj))
(setq coords (list 
(list 5120.5625 -169.554) 
(list 5194.585 -170.004) 
(list 5194.585 -169.827) 
(list 5120.5625 -169.477)))
(apply 'command (append '("pline") coords '("c")))
(setq currobj (ssadd (entlast) currobj))
(setq coords (list 
(list 5120.5625 -169.334) 
(list 5194.585 -169.684) 
(list 5194.585 -169.507) 
(list 5120.5625 -169.257)))
(apply 'command (append '("pline") coords '("c")))
(setq currobj (ssadd (entlast) currobj))
(setq coords (list 
(list 5120.5625 -169.114) 
(list 5194.585 -169.364) 
(list 5194.585 -169.187) 
(list 5120.5625 -169.037)))
(apply 'command (append '("pline") coords '("c")))
(setq currobj (ssadd (entlast) currobj))
(setq coords (list 
(list 5120.5625 -168.894) 
(list 5194.585 -169.044) 
(list 5194.585 -168.867) 
(list 5120.5625 -168.817)))
(apply 'command (append '("pline") coords '("c")))
(setq currobj (ssadd (entlast) currobj))
(setq coords (list 
(list 5120.5625 -168.674) 
(list 5194.585 -168.724) 
(list 5194.585 -168.547) 
(list 5120.5625 -168.597)))
(apply 'command (append '("pline") coords '("c")))
(setq currobj (ssadd (entlast) currobj))
(setq coords (list 
(list 5120.5625 -168.454) 
(list 5194.585 -168.404) 
(list 5194.585 -168.227) 
(list 5120.5625 -168.377)))
(apply 'command (append '("pline") coords '("c")))
(setq currobj (ssadd (entlast) currobj))
(setq coords (list 
(list 5120.5625 -168.234) 
(list 5194.585 -168.084) 
(list 5194.585 -167.907) 
(list 5120.5625 -168.157)))
(apply 'command (append '("pline") coords '("c")))
(setq currobj (ssadd (entlast) currobj))
(setq coords (list 
(list 5120.5625 -168.014) 
(list 5194.585 -167.764) 
(list 5194.585 -167.587) 
(list 5120.5625 -167.937)))
(apply 'command (append '("pline") coords '("c")))
(setq currobj (ssadd (entlast) currobj))
(setq coords (list 
(list 5120.5625 -167.794) 
(list 5194.585 -167.444) 
(list 5194.585 -167.267) 
(list 5120.5625 -167.717)))
(apply 'command (append '("pline") coords '("c")))
(setq currobj (ssadd (entlast) currobj))
(setq coords (list 
(list 5120.5625 -167.574) 
(list 5194.585 -167.124) 
(list 5194.585 -166.947) 
(list 5120.5625 -167.497)))
(apply 'command (append '("pline") coords '("c")))
(setq currobj (ssadd (entlast) currobj))
(setq coords (list 
(list 5120.5625 -167.354) 
(list 5194.585 -166.804) 
(list 5194.585 -166.627) 
(list 5120.5625 -167.277)))
(apply 'command (append '("pline") coords '("c")))
(setq currobj (ssadd (entlast) currobj))
(setq coords (list 
(list 5120.5625 -167.134) 
(list 5194.585 -166.484) 
(list 5194.585 -166.307) 
(list 5120.5625 -167.057)))
(apply 'command (append '("pline") coords '("c")))
(setq currobj (ssadd (entlast) currobj))
(setq coords (list 
(list 5119.4375 -167.057) 
(list 5045.415 -166.307) 
(list 5045.415 -166.484) 
(list 5119.4375 -167.134)))
(apply 'command (append '("pline") coords '("c")))
(setq currobj (ssadd (entlast) currobj))
(setq coords (list 
(list 5119.4375 -167.277) 
(list 5045.415 -166.627) 
(list 5045.415 -166.804) 
(list 5119.4375 -167.354)))
(apply 'command (append '("pline") coords '("c")))
(setq currobj (ssadd (entlast) currobj))
(setq coords (list 
(list 5119.4375 -167.497) 
(list 5045.415 -166.947) 
(list 5045.415 -167.124) 
(list 5119.4375 -167.574)))
(apply 'command (append '("pline") coords '("c")))
(setq currobj (ssadd (entlast) currobj))
(setq coords (list 
(list 5119.4375 -167.717) 
(list 5045.415 -167.267) 
(list 5045.415 -167.444) 
(list 5119.4375 -167.794)))
(apply 'command (append '("pline") coords '("c")))
(setq currobj (ssadd (entlast) currobj))
(setq coords (list 
(list 5119.4375 -167.937) 
(list 5045.415 -167.587) 
(list 5045.415 -167.764) 
(list 5119.4375 -168.014)))
(apply 'command (append '("pline") coords '("c")))
(setq currobj (ssadd (entlast) currobj))
(setq coords (list 
(list 5119.4375 -168.157) 
(list 5045.415 -167.907) 
(list 5045.415 -168.084) 
(list 5119.4375 -168.234)))
(apply 'command (append '("pline") coords '("c")))
(setq currobj (ssadd (entlast) currobj))
(setq coords (list 
(list 5119.4375 -168.377) 
(list 5045.415 -168.227) 
(list 5045.415 -168.404) 
(list 5119.4375 -168.454)))
(apply 'command (append '("pline") coords '("c")))
(setq currobj (ssadd (entlast) currobj))
(setq coords (list 
(list 5119.4375 -168.597) 
(list 5045.415 -168.547) 
(list 5045.415 -168.724) 
(list 5119.4375 -168.674)))
(apply 'command (append '("pline") coords '("c")))
(setq currobj (ssadd (entlast) currobj))
(setq coords (list 
(list 5119.4375 -168.817) 
(list 5045.415 -168.867) 
(list 5045.415 -169.044) 
(list 5119.4375 -168.894)))
(apply 'command (append '("pline") coords '("c")))
(setq currobj (ssadd (entlast) currobj))
(setq coords (list 
(list 5119.4375 -169.037) 
(list 5045.415 -169.187) 
(list 5045.415 -169.364) 
(list 5119.4375 -169.114)))
(apply 'command (append '("pline") coords '("c")))
(setq currobj (ssadd (entlast) currobj))
(setq coords (list 
(list 5119.4375 -169.257) 
(list 5045.415 -169.507) 
(list 5045.415 -169.684) 
(list 5119.4375 -169.334)))
(apply 'command (append '("pline") coords '("c")))
(setq currobj (ssadd (entlast) currobj))
(setq coords (list 
(list 5119.4375 -169.477) 
(list 5045.415 -169.827) 
(list 5045.415 -170.004) 
(list 5119.4375 -169.554)))
(apply 'command (append '("pline") coords '("c")))
(setq currobj (ssadd (entlast) currobj))
(setq coords (list 
(list 5119.4375 -169.697) 
(list 5045.415 -170.147) 
(list 5045.415 -170.324) 
(list 5119.4375 -169.774)))
(apply 'command (append '("pline") coords '("c")))
(setq currobj (ssadd (entlast) currobj))
(setq coords (list 
(list 5119.4375 -169.917) 
(list 5045.415 -170.467) 
(list 5045.415 -170.644) 
(list 5119.4375 -169.994)))
(apply 'command (append '("pline") coords '("c")))
(setq currobj (ssadd (entlast) currobj))
(setq coords (list 
(list 5119.4375 -170.137) 
(list 5045.415 -170.787) 
(list 5045.415 -170.964) 
(list 5119.4375 -170.214)))
(apply 'command (append '("pline") coords '("c")))
(setq currobj (ssadd (entlast) currobj))
(command "_layer" "set" "nitride" "")
(command "_layer" "set" "text" "")
(command "_circle" "5119.0625,-181.357" "0.075")
(command "_circle" "5119.0625,-181.057" "0.075")
(command "_circle" "5119.0625,-180.757" "0.075")
(command "_circle" "5119.0625,-180.457" "0.075")
(command "_circle" "5119.0625,-180.157" "0.075")
(command "_circle" "5118.7625,-181.357" "0.075")
(command "_circle" "5118.7625,-181.057" "0.075")
(command "_circle" "5118.7625,-180.757" "0.075")
(command "_circle" "5118.7625,-180.457" "0.075")
(command "_circle" "5118.7625,-180.157" "0.075")
(command "_circle" "5118.4625,-181.357" "0.075")
(command "_circle" "5118.4625,-181.057" "0.075")
(command "_circle" "5118.4625,-180.757" "0.075")
(command "_circle" "5118.4625,-180.457" "0.075")
(command "_circle" "5118.4625,-180.157" "0.075")
(command "_circle" "5118.1625,-181.357" "0.075")
(command "_circle" "5118.1625,-181.057" "0.075")
(command "_circle" "5118.1625,-180.757" "0.075")
(command "_circle" "5118.1625,-180.457" "0.075")
(command "_circle" "5118.1625,-180.157" "0.075")
(command "_circle" "5117.8625,-181.357" "0.075")
(command "_circle" "5117.8625,-181.057" "0.075")
(command "_circle" "5117.8625,-180.757" "0.075")
(command "_circle" "5117.8625,-180.457" "0.075")
(command "_circle" "5117.8625,-180.157" "0.075")
(command "_layer" "set" "nitride" "")
(setq coords (list 
(list 5120.2625 -155.914) 
(list 5120.2625 -40.2693) 
(list 5119.7375 -40.2693) 
(list 5119.7375 -155.914)))
(apply 'command (append '("pline") coords '("c")))
(setq currobj (ssadd (entlast) currobj))
(command "_layer" "set" "prebias" "")
(command "_rectangle" "5119.7375,-155.914" "5120.2625,-40.2693")
(setq currobj (ssadd (entlast) currobj))
(command "_layer" "set" "nitride" "")
(setq coords (list 
(list 5120.2625 -40.2693) 
(list 5120.5625 -30.2693) 
(list 5120.5625 -30.2693) 
(list 5120.5625 -29.2693) 
(list 5194.585 -30.0193) 
(list 5194.585 -25.0763) 
(list 5120.5625 -25.8263) 
(list 5120.5625 -24.8263) 
(list 5120.5625 -24.8263) 
(list 5120.2625 -14.8263) 
(list 5119.7375 -14.8263) 
(list 5119.4375 -24.8263) 
(list 5119.4375 -24.8263) 
(list 5119.4375 -25.8263) 
(list 5045.415 -25.0763) 
(list 5045.415 -30.0193) 
(list 5119.4375 -29.2693) 
(list 5119.4375 -30.2693) 
(list 5119.4375 -30.2693) 
(list 5119.7375 -40.2693)))
(apply 'command (append '("pline") coords '("c")))
(setq currobj (ssadd (entlast) currobj))
(command "_layer" "set" "prebias" "")
(setq coords (list 
(list 5119.4375 -40.2693) 
(list 5119.4375 -29.2693) 
(list 5045.415 -30.0193) 
(list 5045.415 -25.0763) 
(list 5119.4375 -25.8263) 
(list 5119.4375 -14.8263) 
(list 5120.5625 -14.8263) 
(list 5120.5625 -25.8263) 
(list 5194.585 -25.0763) 
(list 5194.585 -30.0193) 
(list 5120.5625 -29.2693) 
(list 5120.5625 -40.2693)))
(apply 'command (append '("pline") coords '("c")))
(setq currobj (ssadd (entlast) currobj))
(command "_layer" "set" "nitride" "")
(command "_layer" "set" "fda1" "")
(setq coords (list 
(list 5120.5625 -29.1263) 
(list 5194.585 -29.8763) 
(list 5194.585 -29.6993) 
(list 5120.5625 -29.0493)))
(apply 'command (append '("pline") coords '("c")))
(setq currobj (ssadd (entlast) currobj))
(setq coords (list 
(list 5120.5625 -28.9063) 
(list 5194.585 -29.5563) 
(list 5194.585 -29.3793) 
(list 5120.5625 -28.8293)))
(apply 'command (append '("pline") coords '("c")))
(setq currobj (ssadd (entlast) currobj))
(setq coords (list 
(list 5120.5625 -28.6863) 
(list 5194.585 -29.2363) 
(list 5194.585 -29.0593) 
(list 5120.5625 -28.6093)))
(apply 'command (append '("pline") coords '("c")))
(setq currobj (ssadd (entlast) currobj))
(setq coords (list 
(list 5120.5625 -28.4663) 
(list 5194.585 -28.9163) 
(list 5194.585 -28.7393) 
(list 5120.5625 -28.3893)))
(apply 'command (append '("pline") coords '("c")))
(setq currobj (ssadd (entlast) currobj))
(setq coords (list 
(list 5120.5625 -28.2463) 
(list 5194.585 -28.5963) 
(list 5194.585 -28.4193) 
(list 5120.5625 -28.1693)))
(apply 'command (append '("pline") coords '("c")))
(setq currobj (ssadd (entlast) currobj))
(setq coords (list 
(list 5120.5625 -28.0263) 
(list 5194.585 -28.2763) 
(list 5194.585 -28.0993) 
(list 5120.5625 -27.9493)))
(apply 'command (append '("pline") coords '("c")))
(setq currobj (ssadd (entlast) currobj))
(setq coords (list 
(list 5120.5625 -27.8063) 
(list 5194.585 -27.9563) 
(list 5194.585 -27.7793) 
(list 5120.5625 -27.7293)))
(apply 'command (append '("pline") coords '("c")))
(setq currobj (ssadd (entlast) currobj))
(setq coords (list 
(list 5120.5625 -27.5863) 
(list 5194.585 -27.6363) 
(list 5194.585 -27.4593) 
(list 5120.5625 -27.5093)))
(apply 'command (append '("pline") coords '("c")))
(setq currobj (ssadd (entlast) currobj))
(setq coords (list 
(list 5120.5625 -27.3663) 
(list 5194.585 -27.3163) 
(list 5194.585 -27.1393) 
(list 5120.5625 -27.2893)))
(apply 'command (append '("pline") coords '("c")))
(setq currobj (ssadd (entlast) currobj))
(setq coords (list 
(list 5120.5625 -27.1463) 
(list 5194.585 -26.9963) 
(list 5194.585 -26.8193) 
(list 5120.5625 -27.0693)))
(apply 'command (append '("pline") coords '("c")))
(setq currobj (ssadd (entlast) currobj))
(setq coords (list 
(list 5120.5625 -26.9263) 
(list 5194.585 -26.6763) 
(list 5194.585 -26.4993) 
(list 5120.5625 -26.8493)))
(apply 'command (append '("pline") coords '("c")))
(setq currobj (ssadd (entlast) currobj))
(setq coords (list 
(list 5120.5625 -26.7063) 
(list 5194.585 -26.3563) 
(list 5194.585 -26.1793) 
(list 5120.5625 -26.6293)))
(apply 'command (append '("pline") coords '("c")))
(setq currobj (ssadd (entlast) currobj))
(setq coords (list 
(list 5120.5625 -26.4863) 
(list 5194.585 -26.0363) 
(list 5194.585 -25.8593) 
(list 5120.5625 -26.4093)))
(apply 'command (append '("pline") coords '("c")))
(setq currobj (ssadd (entlast) currobj))
(setq coords (list 
(list 5120.5625 -26.2663) 
(list 5194.585 -25.7163) 
(list 5194.585 -25.5393) 
(list 5120.5625 -26.1893)))
(apply 'command (append '("pline") coords '("c")))
(setq currobj (ssadd (entlast) currobj))
(setq coords (list 
(list 5120.5625 -26.0463) 
(list 5194.585 -25.3963) 
(list 5194.585 -25.2193) 
(list 5120.5625 -25.9693)))
(apply 'command (append '("pline") coords '("c")))
(setq currobj (ssadd (entlast) currobj))
(setq coords (list 
(list 5119.4375 -25.9693) 
(list 5045.415 -25.2193) 
(list 5045.415 -25.3963) 
(list 5119.4375 -26.0463)))
(apply 'command (append '("pline") coords '("c")))
(setq currobj (ssadd (entlast) currobj))
(setq coords (list 
(list 5119.4375 -26.1893) 
(list 5045.415 -25.5393) 
(list 5045.415 -25.7163) 
(list 5119.4375 -26.2663)))
(apply 'command (append '("pline") coords '("c")))
(setq currobj (ssadd (entlast) currobj))
(setq coords (list 
(list 5119.4375 -26.4093) 
(list 5045.415 -25.8593) 
(list 5045.415 -26.0363) 
(list 5119.4375 -26.4863)))
(apply 'command (append '("pline") coords '("c")))
(setq currobj (ssadd (entlast) currobj))
(setq coords (list 
(list 5119.4375 -26.6293) 
(list 5045.415 -26.1793) 
(list 5045.415 -26.3563) 
(list 5119.4375 -26.7063)))
(apply 'command (append '("pline") coords '("c")))
(setq currobj (ssadd (entlast) currobj))
(setq coords (list 
(list 5119.4375 -26.8493) 
(list 5045.415 -26.4993) 
(list 5045.415 -26.6763) 
(list 5119.4375 -26.9263)))
(apply 'command (append '("pline") coords '("c")))
(setq currobj (ssadd (entlast) currobj))
(setq coords (list 
(list 5119.4375 -27.0693) 
(list 5045.415 -26.8193) 
(list 5045.415 -26.9963) 
(list 5119.4375 -27.1463)))
(apply 'command (append '("pline") coords '("c")))
(setq currobj (ssadd (entlast) currobj))
(setq coords (list 
(list 5119.4375 -27.2893) 
(list 5045.415 -27.1393) 
(list 5045.415 -27.3163) 
(list 5119.4375 -27.3663)))
(apply 'command (append '("pline") coords '("c")))
(setq currobj (ssadd (entlast) currobj))
(setq coords (list 
(list 5119.4375 -27.5093) 
(list 5045.415 -27.4593) 
(list 5045.415 -27.6363) 
(list 5119.4375 -27.5863)))
(apply 'command (append '("pline") coords '("c")))
(setq currobj (ssadd (entlast) currobj))
(setq coords (list 
(list 5119.4375 -27.7293) 
(list 5045.415 -27.7793) 
(list 5045.415 -27.9563) 
(list 5119.4375 -27.8063)))
(apply 'command (append '("pline") coords '("c")))
(setq currobj (ssadd (entlast) currobj))
(setq coords (list 
(list 5119.4375 -27.9493) 
(list 5045.415 -28.0993) 
(list 5045.415 -28.2763) 
(list 5119.4375 -28.0263)))
(apply 'command (append '("pline") coords '("c")))
(setq currobj (ssadd (entlast) currobj))
(setq coords (list 
(list 5119.4375 -28.1693) 
(list 5045.415 -28.4193) 
(list 5045.415 -28.5963) 
(list 5119.4375 -28.2463)))
(apply 'command (append '("pline") coords '("c")))
(setq currobj (ssadd (entlast) currobj))
(setq coords (list 
(list 5119.4375 -28.3893) 
(list 5045.415 -28.7393) 
(list 5045.415 -28.9163) 
(list 5119.4375 -28.4663)))
(apply 'command (append '("pline") coords '("c")))
(setq currobj (ssadd (entlast) currobj))
(setq coords (list 
(list 5119.4375 -28.6093) 
(list 5045.415 -29.0593) 
(list 5045.415 -29.2363) 
(list 5119.4375 -28.6863)))
(apply 'command (append '("pline") coords '("c")))
(setq currobj (ssadd (entlast) currobj))
(setq coords (list 
(list 5119.4375 -28.8293) 
(list 5045.415 -29.3793) 
(list 5045.415 -29.5563) 
(list 5119.4375 -28.9063)))
(apply 'command (append '("pline") coords '("c")))
(setq currobj (ssadd (entlast) currobj))
(setq coords (list 
(list 5119.4375 -29.0493) 
(list 5045.415 -29.6993) 
(list 5045.415 -29.8763) 
(list 5119.4375 -29.1263)))
(apply 'command (append '("pline") coords '("c")))
(setq currobj (ssadd (entlast) currobj))
(command "_layer" "set" "nitride" "")
(command "_layer" "set" "text" "")
(command "_circle" "5119.0625,-40.2693" "0.075")
(command "_circle" "5119.0625,-39.9693" "0.075")
(command "_circle" "5119.0625,-39.6693" "0.075")
(command "_circle" "5119.0625,-39.3693" "0.075")
(command "_circle" "5119.0625,-39.0693" "0.075")
(command "_circle" "5118.7625,-40.2693" "0.075")
(command "_circle" "5118.7625,-39.9693" "0.075")
(command "_circle" "5118.7625,-39.6693" "0.075")
(command "_circle" "5118.7625,-39.3693" "0.075")
(command "_circle" "5118.7625,-39.0693" "0.075")
(command "_circle" "5118.4625,-40.2693" "0.075")
(command "_circle" "5118.4625,-39.9693" "0.075")
(command "_circle" "5118.4625,-39.6693" "0.075")
(command "_circle" "5118.4625,-39.3693" "0.075")
(command "_circle" "5118.4625,-39.0693" "0.075")
(command "_circle" "5118.1625,-40.2693" "0.075")
(command "_circle" "5118.1625,-39.9693" "0.075")
(command "_circle" "5118.1625,-39.6693" "0.075")
(command "_circle" "5118.1625,-39.3693" "0.075")
(command "_circle" "5118.1625,-39.0693" "0.075")
(command "_circle" "5117.8625,-40.2693" "0.075")
(command "_circle" "5117.8625,-39.9693" "0.075")
(command "_circle" "5117.8625,-39.6693" "0.075")
(command "_circle" "5117.8625,-39.3693" "0.075")
(command "_circle" "5117.8625,-39.0693" "0.075")
(command "_layer" "set" "nitride" "")
(setq coords (list 
(list 5120.2625 -14.8263) 
(list 5120.2625 100.8184) 
(list 5119.7375 100.8184) 
(list 5119.7375 -14.8263)))
(apply 'command (append '("pline") coords '("c")))
(setq currobj (ssadd (entlast) currobj))
(command "_layer" "set" "prebias" "")
(command "_rectangle" "5119.7375,-14.8263" "5120.2625,100.8184")
(setq currobj (ssadd (entlast) currobj))
(command "_layer" "set" "nitride" "")
(setq coords (list 
(list 5120.2625 100.8184) 
(list 5120.5625 110.8184) 
(list 5120.5625 110.8184) 
(list 5120.5625 111.8184) 
(list 5194.585 111.0684) 
(list 5194.585 116.0114) 
(list 5120.5625 115.2614) 
(list 5120.5625 116.2614) 
(list 5120.5625 116.2614) 
(list 5120.2625 126.2614) 
(list 5119.7375 126.2614) 
(list 5119.4375 116.2614) 
(list 5119.4375 116.2614) 
(list 5119.4375 115.2614) 
(list 5045.415 116.0114) 
(list 5045.415 111.0684) 
(list 5119.4375 111.8184) 
(list 5119.4375 110.8184) 
(list 5119.4375 110.8184) 
(list 5119.7375 100.8184)))
(apply 'command (append '("pline") coords '("c")))
(setq currobj (ssadd (entlast) currobj))
(command "_layer" "set" "prebias" "")
(setq coords (list 
(list 5119.4375 100.8184) 
(list 5119.4375 111.8184) 
(list 5045.415 111.0684) 
(list 5045.415 116.0114) 
(list 5119.4375 115.2614) 
(list 5119.4375 126.2614) 
(list 5120.5625 126.2614) 
(list 5120.5625 115.2614) 
(list 5194.585 116.0114) 
(list 5194.585 111.0684) 
(list 5120.5625 111.8184) 
(list 5120.5625 100.8184)))
(apply 'command (append '("pline") coords '("c")))
(setq currobj (ssadd (entlast) currobj))
(command "_layer" "set" "nitride" "")
(command "_layer" "set" "fda1" "")
(setq coords (list 
(list 5120.5625 111.9614) 
(list 5194.585 111.2114) 
(list 5194.585 111.3884) 
(list 5120.5625 112.0384)))
(apply 'command (append '("pline") coords '("c")))
(setq currobj (ssadd (entlast) currobj))
(setq coords (list 
(list 5120.5625 112.1814) 
(list 5194.585 111.5314) 
(list 5194.585 111.7084) 
(list 5120.5625 112.2584)))
(apply 'command (append '("pline") coords '("c")))
(setq currobj (ssadd (entlast) currobj))
(setq coords (list 
(list 5120.5625 112.4014) 
(list 5194.585 111.8514) 
(list 5194.585 112.0284) 
(list 5120.5625 112.4784)))
(apply 'command (append '("pline") coords '("c")))
(setq currobj (ssadd (entlast) currobj))
(setq coords (list 
(list 5120.5625 112.6214) 
(list 5194.585 112.1714) 
(list 5194.585 112.3484) 
(list 5120.5625 112.6984)))
(apply 'command (append '("pline") coords '("c")))
(setq currobj (ssadd (entlast) currobj))
(setq coords (list 
(list 5120.5625 112.8414) 
(list 5194.585 112.4914) 
(list 5194.585 112.6684) 
(list 5120.5625 112.9184)))
(apply 'command (append '("pline") coords '("c")))
(setq currobj (ssadd (entlast) currobj))
(setq coords (list 
(list 5120.5625 113.0614) 
(list 5194.585 112.8114) 
(list 5194.585 112.9884) 
(list 5120.5625 113.1384)))
(apply 'command (append '("pline") coords '("c")))
(setq currobj (ssadd (entlast) currobj))
(setq coords (list 
(list 5120.5625 113.2814) 
(list 5194.585 113.1314) 
(list 5194.585 113.3084) 
(list 5120.5625 113.3584)))
(apply 'command (append '("pline") coords '("c")))
(setq currobj (ssadd (entlast) currobj))
(setq coords (list 
(list 5120.5625 113.5014) 
(list 5194.585 113.4514) 
(list 5194.585 113.6284) 
(list 5120.5625 113.5784)))
(apply 'command (append '("pline") coords '("c")))
(setq currobj (ssadd (entlast) currobj))
(setq coords (list 
(list 5120.5625 113.7214) 
(list 5194.585 113.7714) 
(list 5194.585 113.9484) 
(list 5120.5625 113.7984)))
(apply 'command (append '("pline") coords '("c")))
(setq currobj (ssadd (entlast) currobj))
(setq coords (list 
(list 5120.5625 113.9414) 
(list 5194.585 114.0914) 
(list 5194.585 114.2684) 
(list 5120.5625 114.0184)))
(apply 'command (append '("pline") coords '("c")))
(setq currobj (ssadd (entlast) currobj))
(setq coords (list 
(list 5120.5625 114.1614) 
(list 5194.585 114.4114) 
(list 5194.585 114.5884) 
(list 5120.5625 114.2384)))
(apply 'command (append '("pline") coords '("c")))
(setq currobj (ssadd (entlast) currobj))
(setq coords (list 
(list 5120.5625 114.3814) 
(list 5194.585 114.7314) 
(list 5194.585 114.9084) 
(list 5120.5625 114.4584)))
(apply 'command (append '("pline") coords '("c")))
(setq currobj (ssadd (entlast) currobj))
(setq coords (list 
(list 5120.5625 114.6014) 
(list 5194.585 115.0514) 
(list 5194.585 115.2284) 
(list 5120.5625 114.6784)))
(apply 'command (append '("pline") coords '("c")))
(setq currobj (ssadd (entlast) currobj))
(setq coords (list 
(list 5120.5625 114.8214) 
(list 5194.585 115.3714) 
(list 5194.585 115.5484) 
(list 5120.5625 114.8984)))
(apply 'command (append '("pline") coords '("c")))
(setq currobj (ssadd (entlast) currobj))
(setq coords (list 
(list 5120.5625 115.0414) 
(list 5194.585 115.6914) 
(list 5194.585 115.8684) 
(list 5120.5625 115.1184)))
(apply 'command (append '("pline") coords '("c")))
(setq currobj (ssadd (entlast) currobj))
(setq coords (list 
(list 5119.4375 115.1184) 
(list 5045.415 115.8684) 
(list 5045.415 115.6914) 
(list 5119.4375 115.0414)))
(apply 'command (append '("pline") coords '("c")))
(setq currobj (ssadd (entlast) currobj))
(setq coords (list 
(list 5119.4375 114.8984) 
(list 5045.415 115.5484) 
(list 5045.415 115.3714) 
(list 5119.4375 114.8214)))
(apply 'command (append '("pline") coords '("c")))
(setq currobj (ssadd (entlast) currobj))
(setq coords (list 
(list 5119.4375 114.6784) 
(list 5045.415 115.2284) 
(list 5045.415 115.0514) 
(list 5119.4375 114.6014)))
(apply 'command (append '("pline") coords '("c")))
(setq currobj (ssadd (entlast) currobj))
(setq coords (list 
(list 5119.4375 114.4584) 
(list 5045.415 114.9084) 
(list 5045.415 114.7314) 
(list 5119.4375 114.3814)))
(apply 'command (append '("pline") coords '("c")))
(setq currobj (ssadd (entlast) currobj))
(setq coords (list 
(list 5119.4375 114.2384) 
(list 5045.415 114.5884) 
(list 5045.415 114.4114) 
(list 5119.4375 114.1614)))
(apply 'command (append '("pline") coords '("c")))
(setq currobj (ssadd (entlast) currobj))
(setq coords (list 
(list 5119.4375 114.0184) 
(list 5045.415 114.2684) 
(list 5045.415 114.0914) 
(list 5119.4375 113.9414)))
(apply 'command (append '("pline") coords '("c")))
(setq currobj (ssadd (entlast) currobj))
(setq coords (list 
(list 5119.4375 113.7984) 
(list 5045.415 113.9484) 
(list 5045.415 113.7714) 
(list 5119.4375 113.7214)))
(apply 'command (append '("pline") coords '("c")))
(setq currobj (ssadd (entlast) currobj))
(setq coords (list 
(list 5119.4375 113.5784) 
(list 5045.415 113.6284) 
(list 5045.415 113.4514) 
(list 5119.4375 113.5014)))
(apply 'command (append '("pline") coords '("c")))
(setq currobj (ssadd (entlast) currobj))
(setq coords (list 
(list 5119.4375 113.3584) 
(list 5045.415 113.3084) 
(list 5045.415 113.1314) 
(list 5119.4375 113.2814)))
(apply 'command (append '("pline") coords '("c")))
(setq currobj (ssadd (entlast) currobj))
(setq coords (list 
(list 5119.4375 113.1384) 
(list 5045.415 112.9884) 
(list 5045.415 112.8114) 
(list 5119.4375 113.0614)))
(apply 'command (append '("pline") coords '("c")))
(setq currobj (ssadd (entlast) currobj))
(setq coords (list 
(list 5119.4375 112.9184) 
(list 5045.415 112.6684) 
(list 5045.415 112.4914) 
(list 5119.4375 112.8414)))
(apply 'command (append '("pline") coords '("c")))
(setq currobj (ssadd (entlast) currobj))
(setq coords (list 
(list 5119.4375 112.6984) 
(list 5045.415 112.3484) 
(list 5045.415 112.1714) 
(list 5119.4375 112.6214)))
(apply 'command (append '("pline") coords '("c")))
(setq currobj (ssadd (entlast) currobj))
(setq coords (list 
(list 5119.4375 112.4784) 
(list 5045.415 112.0284) 
(list 5045.415 111.8514) 
(list 5119.4375 112.4014)))
(apply 'command (append '("pline") coords '("c")))
(setq currobj (ssadd (entlast) currobj))
(setq coords (list 
(list 5119.4375 112.2584) 
(list 5045.415 111.7084) 
(list 5045.415 111.5314) 
(list 5119.4375 112.1814)))
(apply 'command (append '("pline") coords '("c")))
(setq currobj (ssadd (entlast) currobj))
(setq coords (list 
(list 5119.4375 112.0384) 
(list 5045.415 111.3884) 
(list 5045.415 111.2114) 
(list 5119.4375 111.9614)))
(apply 'command (append '("pline") coords '("c")))
(setq currobj (ssadd (entlast) currobj))
(command "_layer" "set" "nitride" "")
(command "_layer" "set" "text" "")
(command "_circle" "5119.0625,100.8184" "0.075")
(command "_circle" "5119.0625,101.1184" "0.075")
(command "_circle" "5119.0625,101.4184" "0.075")
(command "_circle" "5119.0625,101.7184" "0.075")
(command "_circle" "5119.0625,102.0184" "0.075")
(command "_circle" "5118.7625,100.8184" "0.075")
(command "_circle" "5118.7625,101.1184" "0.075")
(command "_circle" "5118.7625,101.4184" "0.075")
(command "_circle" "5118.7625,101.7184" "0.075")
(command "_circle" "5118.7625,102.0184" "0.075")
(command "_circle" "5118.4625,100.8184" "0.075")
(command "_circle" "5118.4625,101.1184" "0.075")
(command "_circle" "5118.4625,101.4184" "0.075")
(command "_circle" "5118.4625,101.7184" "0.075")
(command "_circle" "5118.4625,102.0184" "0.075")
(command "_circle" "5118.1625,100.8184" "0.075")
(command "_circle" "5118.1625,101.1184" "0.075")
(command "_circle" "5118.1625,101.4184" "0.075")
(command "_circle" "5118.1625,101.7184" "0.075")
(command "_circle" "5118.1625,102.0184" "0.075")
(command "_circle" "5117.8625,100.8184" "0.075")
(command "_circle" "5117.8625,101.1184" "0.075")
(command "_circle" "5117.8625,101.4184" "0.075")
(command "_circle" "5117.8625,101.7184" "0.075")
(command "_circle" "5117.8625,102.0184" "0.075")
(command "_layer" "set" "nitride" "")
(setq coords (list 
(list 5120.2625 126.2614) 
(list 5120.2625 241.9061) 
(list 5119.7375 241.9061) 
(list 5119.7375 126.2614)))
(apply 'command (append '("pline") coords '("c")))
(setq currobj (ssadd (entlast) currobj))
(command "_layer" "set" "prebias" "")
(command "_rectangle" "5119.7375,126.2614" "5120.2625,241.9061")
(setq currobj (ssadd (entlast) currobj))
(command "_layer" "set" "nitride" "")
(setq coords (list 
(list 5120.2625 241.9061) 
(list 5120.5625 251.9061) 
(list 5120.5625 251.9061) 
(list 5120.5625 252.9061) 
(list 5194.585 252.1561) 
(list 5194.585 257.0991) 
(list 5120.5625 256.3491) 
(list 5120.5625 257.3491) 
(list 5120.5625 257.3491) 
(list 5120.2625 267.3491) 
(list 5119.7375 267.3491) 
(list 5119.4375 257.3491) 
(list 5119.4375 257.3491) 
(list 5119.4375 256.3491) 
(list 5045.415 257.0991) 
(list 5045.415 252.1561) 
(list 5119.4375 252.9061) 
(list 5119.4375 251.9061) 
(list 5119.4375 251.9061) 
(list 5119.7375 241.9061)))
(apply 'command (append '("pline") coords '("c")))
(setq currobj (ssadd (entlast) currobj))
(command "_layer" "set" "prebias" "")
(setq coords (list 
(list 5119.4375 241.9061) 
(list 5119.4375 252.9061) 
(list 5045.415 252.1561) 
(list 5045.415 257.0991) 
(list 5119.4375 256.3491) 
(list 5119.4375 267.3491) 
(list 5120.5625 267.3491) 
(list 5120.5625 256.3491) 
(list 5194.585 257.0991) 
(list 5194.585 252.1561) 
(list 5120.5625 252.9061) 
(list 5120.5625 241.9061)))
(apply 'command (append '("pline") coords '("c")))
(setq currobj (ssadd (entlast) currobj))
(command "_layer" "set" "nitride" "")
(command "_layer" "set" "fda1" "")
(setq coords (list 
(list 5120.5625 253.0491) 
(list 5194.585 252.2991) 
(list 5194.585 252.4761) 
(list 5120.5625 253.1261)))
(apply 'command (append '("pline") coords '("c")))
(setq currobj (ssadd (entlast) currobj))
(setq coords (list 
(list 5120.5625 253.2691) 
(list 5194.585 252.6191) 
(list 5194.585 252.7961) 
(list 5120.5625 253.3461)))
(apply 'command (append '("pline") coords '("c")))
(setq currobj (ssadd (entlast) currobj))
(setq coords (list 
(list 5120.5625 253.4891) 
(list 5194.585 252.9391) 
(list 5194.585 253.1161) 
(list 5120.5625 253.5661)))
(apply 'command (append '("pline") coords '("c")))
(setq currobj (ssadd (entlast) currobj))
(setq coords (list 
(list 5120.5625 253.7091) 
(list 5194.585 253.2591) 
(list 5194.585 253.4361) 
(list 5120.5625 253.7861)))
(apply 'command (append '("pline") coords '("c")))
(setq currobj (ssadd (entlast) currobj))
(setq coords (list 
(list 5120.5625 253.9291) 
(list 5194.585 253.5791) 
(list 5194.585 253.7561) 
(list 5120.5625 254.0061)))
(apply 'command (append '("pline") coords '("c")))
(setq currobj (ssadd (entlast) currobj))
(setq coords (list 
(list 5120.5625 254.1491) 
(list 5194.585 253.8991) 
(list 5194.585 254.0761) 
(list 5120.5625 254.2261)))
(apply 'command (append '("pline") coords '("c")))
(setq currobj (ssadd (entlast) currobj))
(setq coords (list 
(list 5120.5625 254.3691) 
(list 5194.585 254.2191) 
(list 5194.585 254.3961) 
(list 5120.5625 254.4461)))
(apply 'command (append '("pline") coords '("c")))
(setq currobj (ssadd (entlast) currobj))
(setq coords (list 
(list 5120.5625 254.5891) 
(list 5194.585 254.5391) 
(list 5194.585 254.7161) 
(list 5120.5625 254.6661)))
(apply 'command (append '("pline") coords '("c")))
(setq currobj (ssadd (entlast) currobj))
(setq coords (list 
(list 5120.5625 254.8091) 
(list 5194.585 254.8591) 
(list 5194.585 255.0361) 
(list 5120.5625 254.8861)))
(apply 'command (append '("pline") coords '("c")))
(setq currobj (ssadd (entlast) currobj))
(setq coords (list 
(list 5120.5625 255.0291) 
(list 5194.585 255.1791) 
(list 5194.585 255.3561) 
(list 5120.5625 255.1061)))
(apply 'command (append '("pline") coords '("c")))
(setq currobj (ssadd (entlast) currobj))
(setq coords (list 
(list 5120.5625 255.2491) 
(list 5194.585 255.4991) 
(list 5194.585 255.6761) 
(list 5120.5625 255.3261)))
(apply 'command (append '("pline") coords '("c")))
(setq currobj (ssadd (entlast) currobj))
(setq coords (list 
(list 5120.5625 255.4691) 
(list 5194.585 255.8191) 
(list 5194.585 255.9961) 
(list 5120.5625 255.5461)))
(apply 'command (append '("pline") coords '("c")))
(setq currobj (ssadd (entlast) currobj))
(setq coords (list 
(list 5120.5625 255.6891) 
(list 5194.585 256.1391) 
(list 5194.585 256.3161) 
(list 5120.5625 255.7661)))
(apply 'command (append '("pline") coords '("c")))
(setq currobj (ssadd (entlast) currobj))
(setq coords (list 
(list 5120.5625 255.9091) 
(list 5194.585 256.4591) 
(list 5194.585 256.6361) 
(list 5120.5625 255.9861)))
(apply 'command (append '("pline") coords '("c")))
(setq currobj (ssadd (entlast) currobj))
(setq coords (list 
(list 5120.5625 256.1291) 
(list 5194.585 256.7791) 
(list 5194.585 256.9561) 
(list 5120.5625 256.2061)))
(apply 'command (append '("pline") coords '("c")))
(setq currobj (ssadd (entlast) currobj))
(setq coords (list 
(list 5119.4375 256.2061) 
(list 5045.415 256.9561) 
(list 5045.415 256.7791) 
(list 5119.4375 256.1291)))
(apply 'command (append '("pline") coords '("c")))
(setq currobj (ssadd (entlast) currobj))
(setq coords (list 
(list 5119.4375 255.9861) 
(list 5045.415 256.6361) 
(list 5045.415 256.4591) 
(list 5119.4375 255.9091)))
(apply 'command (append '("pline") coords '("c")))
(setq currobj (ssadd (entlast) currobj))
(setq coords (list 
(list 5119.4375 255.7661) 
(list 5045.415 256.3161) 
(list 5045.415 256.1391) 
(list 5119.4375 255.6891)))
(apply 'command (append '("pline") coords '("c")))
(setq currobj (ssadd (entlast) currobj))
(setq coords (list 
(list 5119.4375 255.5461) 
(list 5045.415 255.9961) 
(list 5045.415 255.8191) 
(list 5119.4375 255.4691)))
(apply 'command (append '("pline") coords '("c")))
(setq currobj (ssadd (entlast) currobj))
(setq coords (list 
(list 5119.4375 255.3261) 
(list 5045.415 255.6761) 
(list 5045.415 255.4991) 
(list 5119.4375 255.2491)))
(apply 'command (append '("pline") coords '("c")))
(setq currobj (ssadd (entlast) currobj))
(setq coords (list 
(list 5119.4375 255.1061) 
(list 5045.415 255.3561) 
(list 5045.415 255.1791) 
(list 5119.4375 255.0291)))
(apply 'command (append '("pline") coords '("c")))
(setq currobj (ssadd (entlast) currobj))
(setq coords (list 
(list 5119.4375 254.8861) 
(list 5045.415 255.0361) 
(list 5045.415 254.8591) 
(list 5119.4375 254.8091)))
(apply 'command (append '("pline") coords '("c")))
(setq currobj (ssadd (entlast) currobj))
(setq coords (list 
(list 5119.4375 254.6661) 
(list 5045.415 254.7161) 
(list 5045.415 254.5391) 
(list 5119.4375 254.5891)))
(apply 'command (append '("pline") coords '("c")))
(setq currobj (ssadd (entlast) currobj))
(setq coords (list 
(list 5119.4375 254.4461) 
(list 5045.415 254.3961) 
(list 5045.415 254.2191) 
(list 5119.4375 254.3691)))
(apply 'command (append '("pline") coords '("c")))
(setq currobj (ssadd (entlast) currobj))
(setq coords (list 
(list 5119.4375 254.2261) 
(list 5045.415 254.0761) 
(list 5045.415 253.8991) 
(list 5119.4375 254.1491)))
(apply 'command (append '("pline") coords '("c")))
(setq currobj (ssadd (entlast) currobj))
(setq coords (list 
(list 5119.4375 254.0061) 
(list 5045.415 253.7561) 
(list 5045.415 253.5791) 
(list 5119.4375 253.9291)))
(apply 'command (append '("pline") coords '("c")))
(setq currobj (ssadd (entlast) currobj))
(setq coords (list 
(list 5119.4375 253.7861) 
(list 5045.415 253.4361) 
(list 5045.415 253.2591) 
(list 5119.4375 253.7091)))
(apply 'command (append '("pline") coords '("c")))
(setq currobj (ssadd (entlast) currobj))
(setq coords (list 
(list 5119.4375 253.5661) 
(list 5045.415 253.1161) 
(list 5045.415 252.9391) 
(list 5119.4375 253.4891)))
(apply 'command (append '("pline") coords '("c")))
(setq currobj (ssadd (entlast) currobj))
(setq coords (list 
(list 5119.4375 253.3461) 
(list 5045.415 252.7961) 
(list 5045.415 252.6191) 
(list 5119.4375 253.2691)))
(apply 'command (append '("pline") coords '("c")))
(setq currobj (ssadd (entlast) currobj))
(setq coords (list 
(list 5119.4375 253.1261) 
(list 5045.415 252.4761) 
(list 5045.415 252.2991) 
(list 5119.4375 253.0491)))
(apply 'command (append '("pline") coords '("c")))
(setq currobj (ssadd (entlast) currobj))
(command "_layer" "set" "nitride" "")
(command "_layer" "set" "text" "")
(command "_circle" "5119.0625,241.9061" "0.075")
(command "_circle" "5119.0625,242.2061" "0.075")
(command "_circle" "5119.0625,242.5061" "0.075")
(command "_circle" "5119.0625,242.8061" "0.075")
(command "_circle" "5119.0625,243.1061" "0.075")
(command "_circle" "5118.7625,241.9061" "0.075")
(command "_circle" "5118.7625,242.2061" "0.075")
(command "_circle" "5118.7625,242.5061" "0.075")
(command "_circle" "5118.7625,242.8061" "0.075")
(command "_circle" "5118.7625,243.1061" "0.075")
(command "_circle" "5118.4625,241.9061" "0.075")
(command "_circle" "5118.4625,242.2061" "0.075")
(command "_circle" "5118.4625,242.5061" "0.075")
(command "_circle" "5118.4625,242.8061" "0.075")
(command "_circle" "5118.4625,243.1061" "0.075")
(command "_circle" "5118.1625,241.9061" "0.075")
(command "_circle" "5118.1625,242.2061" "0.075")
(command "_circle" "5118.1625,242.5061" "0.075")
(command "_circle" "5118.1625,242.8061" "0.075")
(command "_circle" "5118.1625,243.1061" "0.075")
(command "_circle" "5117.8625,241.9061" "0.075")
(command "_circle" "5117.8625,242.2061" "0.075")
(command "_circle" "5117.8625,242.5061" "0.075")
(command "_circle" "5117.8625,242.8061" "0.075")
(command "_circle" "5117.8625,243.1061" "0.075")
(command "_layer" "set" "nitride" "")
(setq coords (list 
(list 5120.2625 267.3491) 
(list 5120.2625 382.9939) 
(list 5119.7375 382.9939) 
(list 5119.7375 267.3491)))
(apply 'command (append '("pline") coords '("c")))
(setq currobj (ssadd (entlast) currobj))
(command "_layer" "set" "prebias" "")
(command "_rectangle" "5119.7375,267.3491" "5120.2625,382.9939")
(setq currobj (ssadd (entlast) currobj))
(command "_layer" "set" "nitride" "")
(setq coords (list 
(list 5120.2625 382.9939) 
(list 5120.5625 392.9939) 
(list 5120.5625 392.9939) 
(list 5120.5625 393.9939) 
(list 5194.585 393.2439) 
(list 5194.585 398.1869) 
(list 5120.5625 397.4369) 
(list 5120.5625 398.4369) 
(list 5120.5625 398.4369) 
(list 5120.2625 408.4369) 
(list 5119.7375 408.4369) 
(list 5119.4375 398.4369) 
(list 5119.4375 398.4369) 
(list 5119.4375 397.4369) 
(list 5045.415 398.1869) 
(list 5045.415 393.2439) 
(list 5119.4375 393.9939) 
(list 5119.4375 392.9939) 
(list 5119.4375 392.9939) 
(list 5119.7375 382.9939)))
(apply 'command (append '("pline") coords '("c")))
(setq currobj (ssadd (entlast) currobj))
(command "_layer" "set" "prebias" "")
(setq coords (list 
(list 5119.4375 382.9939) 
(list 5119.4375 393.9939) 
(list 5045.415 393.2439) 
(list 5045.415 398.1869) 
(list 5119.4375 397.4369) 
(list 5119.4375 408.4369) 
(list 5120.5625 408.4369) 
(list 5120.5625 397.4369) 
(list 5194.585 398.1869) 
(list 5194.585 393.2439) 
(list 5120.5625 393.9939) 
(list 5120.5625 382.9939)))
(apply 'command (append '("pline") coords '("c")))
(setq currobj (ssadd (entlast) currobj))
(command "_layer" "set" "nitride" "")
(command "_layer" "set" "fda1" "")
(setq coords (list 
(list 5120.5625 394.1369) 
(list 5194.585 393.3869) 
(list 5194.585 393.5639) 
(list 5120.5625 394.2139)))
(apply 'command (append '("pline") coords '("c")))
(setq currobj (ssadd (entlast) currobj))
(setq coords (list 
(list 5120.5625 394.3569) 
(list 5194.585 393.7069) 
(list 5194.585 393.8839) 
(list 5120.5625 394.4339)))
(apply 'command (append '("pline") coords '("c")))
(setq currobj (ssadd (entlast) currobj))
(setq coords (list 
(list 5120.5625 394.5769) 
(list 5194.585 394.0269) 
(list 5194.585 394.2039) 
(list 5120.5625 394.6539)))
(apply 'command (append '("pline") coords '("c")))
(setq currobj (ssadd (entlast) currobj))
(setq coords (list 
(list 5120.5625 394.7969) 
(list 5194.585 394.3469) 
(list 5194.585 394.5239) 
(list 5120.5625 394.8739)))
(apply 'command (append '("pline") coords '("c")))
(setq currobj (ssadd (entlast) currobj))
(setq coords (list 
(list 5120.5625 395.0169) 
(list 5194.585 394.6669) 
(list 5194.585 394.8439) 
(list 5120.5625 395.0939)))
(apply 'command (append '("pline") coords '("c")))
(setq currobj (ssadd (entlast) currobj))
(setq coords (list 
(list 5120.5625 395.2369) 
(list 5194.585 394.9869) 
(list 5194.585 395.1639) 
(list 5120.5625 395.3139)))
(apply 'command (append '("pline") coords '("c")))
(setq currobj (ssadd (entlast) currobj))
(setq coords (list 
(list 5120.5625 395.4569) 
(list 5194.585 395.3069) 
(list 5194.585 395.4839) 
(list 5120.5625 395.5339)))
(apply 'command (append '("pline") coords '("c")))
(setq currobj (ssadd (entlast) currobj))
(setq coords (list 
(list 5120.5625 395.6769) 
(list 5194.585 395.6269) 
(list 5194.585 395.8039) 
(list 5120.5625 395.7539)))
(apply 'command (append '("pline") coords '("c")))
(setq currobj (ssadd (entlast) currobj))
(setq coords (list 
(list 5120.5625 395.8969) 
(list 5194.585 395.9469) 
(list 5194.585 396.1239) 
(list 5120.5625 395.9739)))
(apply 'command (append '("pline") coords '("c")))
(setq currobj (ssadd (entlast) currobj))
(setq coords (list 
(list 5120.5625 396.1169) 
(list 5194.585 396.2669) 
(list 5194.585 396.4439) 
(list 5120.5625 396.1939)))
(apply 'command (append '("pline") coords '("c")))
(setq currobj (ssadd (entlast) currobj))
(setq coords (list 
(list 5120.5625 396.3369) 
(list 5194.585 396.5869) 
(list 5194.585 396.7639) 
(list 5120.5625 396.4139)))
(apply 'command (append '("pline") coords '("c")))
(setq currobj (ssadd (entlast) currobj))
(setq coords (list 
(list 5120.5625 396.5569) 
(list 5194.585 396.9069) 
(list 5194.585 397.0839) 
(list 5120.5625 396.6339)))
(apply 'command (append '("pline") coords '("c")))
(setq currobj (ssadd (entlast) currobj))
(setq coords (list 
(list 5120.5625 396.7769) 
(list 5194.585 397.2269) 
(list 5194.585 397.4039) 
(list 5120.5625 396.8539)))
(apply 'command (append '("pline") coords '("c")))
(setq currobj (ssadd (entlast) currobj))
(setq coords (list 
(list 5120.5625 396.9969) 
(list 5194.585 397.5469) 
(list 5194.585 397.7239) 
(list 5120.5625 397.0739)))
(apply 'command (append '("pline") coords '("c")))
(setq currobj (ssadd (entlast) currobj))
(setq coords (list 
(list 5120.5625 397.2169) 
(list 5194.585 397.8669) 
(list 5194.585 398.0439) 
(list 5120.5625 397.2939)))
(apply 'command (append '("pline") coords '("c")))
(setq currobj (ssadd (entlast) currobj))
(setq coords (list 
(list 5119.4375 397.2939) 
(list 5045.415 398.0439) 
(list 5045.415 397.8669) 
(list 5119.4375 397.2169)))
(apply 'command (append '("pline") coords '("c")))
(setq currobj (ssadd (entlast) currobj))
(setq coords (list 
(list 5119.4375 397.0739) 
(list 5045.415 397.7239) 
(list 5045.415 397.5469) 
(list 5119.4375 396.9969)))
(apply 'command (append '("pline") coords '("c")))
(setq currobj (ssadd (entlast) currobj))
(setq coords (list 
(list 5119.4375 396.8539) 
(list 5045.415 397.4039) 
(list 5045.415 397.2269) 
(list 5119.4375 396.7769)))
(apply 'command (append '("pline") coords '("c")))
(setq currobj (ssadd (entlast) currobj))
(setq coords (list 
(list 5119.4375 396.6339) 
(list 5045.415 397.0839) 
(list 5045.415 396.9069) 
(list 5119.4375 396.5569)))
(apply 'command (append '("pline") coords '("c")))
(setq currobj (ssadd (entlast) currobj))
(setq coords (list 
(list 5119.4375 396.4139) 
(list 5045.415 396.7639) 
(list 5045.415 396.5869) 
(list 5119.4375 396.3369)))
(apply 'command (append '("pline") coords '("c")))
(setq currobj (ssadd (entlast) currobj))
(setq coords (list 
(list 5119.4375 396.1939) 
(list 5045.415 396.4439) 
(list 5045.415 396.2669) 
(list 5119.4375 396.1169)))
(apply 'command (append '("pline") coords '("c")))
(setq currobj (ssadd (entlast) currobj))
(setq coords (list 
(list 5119.4375 395.9739) 
(list 5045.415 396.1239) 
(list 5045.415 395.9469) 
(list 5119.4375 395.8969)))
(apply 'command (append '("pline") coords '("c")))
(setq currobj (ssadd (entlast) currobj))
(setq coords (list 
(list 5119.4375 395.7539) 
(list 5045.415 395.8039) 
(list 5045.415 395.6269) 
(list 5119.4375 395.6769)))
(apply 'command (append '("pline") coords '("c")))
(setq currobj (ssadd (entlast) currobj))
(setq coords (list 
(list 5119.4375 395.5339) 
(list 5045.415 395.4839) 
(list 5045.415 395.3069) 
(list 5119.4375 395.4569)))
(apply 'command (append '("pline") coords '("c")))
(setq currobj (ssadd (entlast) currobj))
(setq coords (list 
(list 5119.4375 395.3139) 
(list 5045.415 395.1639) 
(list 5045.415 394.9869) 
(list 5119.4375 395.2369)))
(apply 'command (append '("pline") coords '("c")))
(setq currobj (ssadd (entlast) currobj))
(setq coords (list 
(list 5119.4375 395.0939) 
(list 5045.415 394.8439) 
(list 5045.415 394.6669) 
(list 5119.4375 395.0169)))
(apply 'command (append '("pline") coords '("c")))
(setq currobj (ssadd (entlast) currobj))
(setq coords (list 
(list 5119.4375 394.8739) 
(list 5045.415 394.5239) 
(list 5045.415 394.3469) 
(list 5119.4375 394.7969)))
(apply 'command (append '("pline") coords '("c")))
(setq currobj (ssadd (entlast) currobj))
(setq coords (list 
(list 5119.4375 394.6539) 
(list 5045.415 394.2039) 
(list 5045.415 394.0269) 
(list 5119.4375 394.5769)))
(apply 'command (append '("pline") coords '("c")))
(setq currobj (ssadd (entlast) currobj))
(setq coords (list 
(list 5119.4375 394.4339) 
(list 5045.415 393.8839) 
(list 5045.415 393.7069) 
(list 5119.4375 394.3569)))
(apply 'command (append '("pline") coords '("c")))
(setq currobj (ssadd (entlast) currobj))
(setq coords (list 
(list 5119.4375 394.2139) 
(list 5045.415 393.5639) 
(list 5045.415 393.3869) 
(list 5119.4375 394.1369)))
(apply 'command (append '("pline") coords '("c")))
(setq currobj (ssadd (entlast) currobj))
(command "_layer" "set" "nitride" "")
(command "_layer" "set" "text" "")
(command "_circle" "5119.0625,382.9939" "0.075")
(command "_circle" "5119.0625,383.2939" "0.075")
(command "_circle" "5119.0625,383.5939" "0.075")
(command "_circle" "5119.0625,383.8939" "0.075")
(command "_circle" "5119.0625,384.1939" "0.075")
(command "_circle" "5118.7625,382.9939" "0.075")
(command "_circle" "5118.7625,383.2939" "0.075")
(command "_circle" "5118.7625,383.5939" "0.075")
(command "_circle" "5118.7625,383.8939" "0.075")
(command "_circle" "5118.7625,384.1939" "0.075")
(command "_circle" "5118.4625,382.9939" "0.075")
(command "_circle" "5118.4625,383.2939" "0.075")
(command "_circle" "5118.4625,383.5939" "0.075")
(command "_circle" "5118.4625,383.8939" "0.075")
(command "_circle" "5118.4625,384.1939" "0.075")
(command "_circle" "5118.1625,382.9939" "0.075")
(command "_circle" "5118.1625,383.2939" "0.075")
(command "_circle" "5118.1625,383.5939" "0.075")
(command "_circle" "5118.1625,383.8939" "0.075")
(command "_circle" "5118.1625,384.1939" "0.075")
(command "_circle" "5117.8625,382.9939" "0.075")
(command "_circle" "5117.8625,383.2939" "0.075")
(command "_circle" "5117.8625,383.5939" "0.075")
(command "_circle" "5117.8625,383.8939" "0.075")
(command "_circle" "5117.8625,384.1939" "0.075")
(command "_layer" "set" "nitride" "")
(setq coords (list 
(list 5120.2625 408.4369) 
(list 5120.2625 524.0816) 
(list 5119.7375 524.0816) 
(list 5119.7375 408.4369)))
(apply 'command (append '("pline") coords '("c")))
(setq currobj (ssadd (entlast) currobj))
(command "_layer" "set" "prebias" "")
(command "_rectangle" "5119.7375,408.4369" "5120.2625,524.0816")
(setq currobj (ssadd (entlast) currobj))
(command "_layer" "set" "nitride" "")
(setq coords (list 
(list 5120.2625 524.0816) 
(list 5120.5625 534.0816) 
(list 5120.5625 534.0816) 
(list 5120.5625 535.0816) 
(list 5194.585 534.3316) 
(list 5194.585 539.2746) 
(list 5120.5625 538.5246) 
(list 5120.5625 539.5246) 
(list 5120.5625 539.5246) 
(list 5120.2625 549.5246) 
(list 5119.7375 549.5246) 
(list 5119.4375 539.5246) 
(list 5119.4375 539.5246) 
(list 5119.4375 538.5246) 
(list 5045.415 539.2746) 
(list 5045.415 534.3316) 
(list 5119.4375 535.0816) 
(list 5119.4375 534.0816) 
(list 5119.4375 534.0816) 
(list 5119.7375 524.0816)))
(apply 'command (append '("pline") coords '("c")))
(setq currobj (ssadd (entlast) currobj))
(command "_layer" "set" "prebias" "")
(setq coords (list 
(list 5119.4375 524.0816) 
(list 5119.4375 535.0816) 
(list 5045.415 534.3316) 
(list 5045.415 539.2746) 
(list 5119.4375 538.5246) 
(list 5119.4375 549.5246) 
(list 5120.5625 549.5246) 
(list 5120.5625 538.5246) 
(list 5194.585 539.2746) 
(list 5194.585 534.3316) 
(list 5120.5625 535.0816) 
(list 5120.5625 524.0816)))
(apply 'command (append '("pline") coords '("c")))
(setq currobj (ssadd (entlast) currobj))
(command "_layer" "set" "nitride" "")
(command "_layer" "set" "fda1" "")
(setq coords (list 
(list 5120.5625 535.2246) 
(list 5194.585 534.4746) 
(list 5194.585 534.6516) 
(list 5120.5625 535.3016)))
(apply 'command (append '("pline") coords '("c")))
(setq currobj (ssadd (entlast) currobj))
(setq coords (list 
(list 5120.5625 535.4446) 
(list 5194.585 534.7946) 
(list 5194.585 534.9716) 
(list 5120.5625 535.5216)))
(apply 'command (append '("pline") coords '("c")))
(setq currobj (ssadd (entlast) currobj))
(setq coords (list 
(list 5120.5625 535.6646) 
(list 5194.585 535.1146) 
(list 5194.585 535.2916) 
(list 5120.5625 535.7416)))
(apply 'command (append '("pline") coords '("c")))
(setq currobj (ssadd (entlast) currobj))
(setq coords (list 
(list 5120.5625 535.8846) 
(list 5194.585 535.4346) 
(list 5194.585 535.6116) 
(list 5120.5625 535.9616)))
(apply 'command (append '("pline") coords '("c")))
(setq currobj (ssadd (entlast) currobj))
(setq coords (list 
(list 5120.5625 536.1046) 
(list 5194.585 535.7546) 
(list 5194.585 535.9316) 
(list 5120.5625 536.1816)))
(apply 'command (append '("pline") coords '("c")))
(setq currobj (ssadd (entlast) currobj))
(setq coords (list 
(list 5120.5625 536.3246) 
(list 5194.585 536.0746) 
(list 5194.585 536.2516) 
(list 5120.5625 536.4016)))
(apply 'command (append '("pline") coords '("c")))
(setq currobj (ssadd (entlast) currobj))
(setq coords (list 
(list 5120.5625 536.5446) 
(list 5194.585 536.3946) 
(list 5194.585 536.5716) 
(list 5120.5625 536.6216)))
(apply 'command (append '("pline") coords '("c")))
(setq currobj (ssadd (entlast) currobj))
(setq coords (list 
(list 5120.5625 536.7646) 
(list 5194.585 536.7146) 
(list 5194.585 536.8916) 
(list 5120.5625 536.8416)))
(apply 'command (append '("pline") coords '("c")))
(setq currobj (ssadd (entlast) currobj))
(setq coords (list 
(list 5120.5625 536.9846) 
(list 5194.585 537.0346) 
(list 5194.585 537.2116) 
(list 5120.5625 537.0616)))
(apply 'command (append '("pline") coords '("c")))
(setq currobj (ssadd (entlast) currobj))
(setq coords (list 
(list 5120.5625 537.2046) 
(list 5194.585 537.3546) 
(list 5194.585 537.5316) 
(list 5120.5625 537.2816)))
(apply 'command (append '("pline") coords '("c")))
(setq currobj (ssadd (entlast) currobj))
(setq coords (list 
(list 5120.5625 537.4246) 
(list 5194.585 537.6746) 
(list 5194.585 537.8516) 
(list 5120.5625 537.5016)))
(apply 'command (append '("pline") coords '("c")))
(setq currobj (ssadd (entlast) currobj))
(setq coords (list 
(list 5120.5625 537.6446) 
(list 5194.585 537.9946) 
(list 5194.585 538.1716) 
(list 5120.5625 537.7216)))
(apply 'command (append '("pline") coords '("c")))
(setq currobj (ssadd (entlast) currobj))
(setq coords (list 
(list 5120.5625 537.8646) 
(list 5194.585 538.3146) 
(list 5194.585 538.4916) 
(list 5120.5625 537.9416)))
(apply 'command (append '("pline") coords '("c")))
(setq currobj (ssadd (entlast) currobj))
(setq coords (list 
(list 5120.5625 538.0846) 
(list 5194.585 538.6346) 
(list 5194.585 538.8116) 
(list 5120.5625 538.1616)))
(apply 'command (append '("pline") coords '("c")))
(setq currobj (ssadd (entlast) currobj))
(setq coords (list 
(list 5120.5625 538.3046) 
(list 5194.585 538.9546) 
(list 5194.585 539.1316) 
(list 5120.5625 538.3816)))
(apply 'command (append '("pline") coords '("c")))
(setq currobj (ssadd (entlast) currobj))
(setq coords (list 
(list 5119.4375 538.3816) 
(list 5045.415 539.1316) 
(list 5045.415 538.9546) 
(list 5119.4375 538.3046)))
(apply 'command (append '("pline") coords '("c")))
(setq currobj (ssadd (entlast) currobj))
(setq coords (list 
(list 5119.4375 538.1616) 
(list 5045.415 538.8116) 
(list 5045.415 538.6346) 
(list 5119.4375 538.0846)))
(apply 'command (append '("pline") coords '("c")))
(setq currobj (ssadd (entlast) currobj))
(setq coords (list 
(list 5119.4375 537.9416) 
(list 5045.415 538.4916) 
(list 5045.415 538.3146) 
(list 5119.4375 537.8646)))
(apply 'command (append '("pline") coords '("c")))
(setq currobj (ssadd (entlast) currobj))
(setq coords (list 
(list 5119.4375 537.7216) 
(list 5045.415 538.1716) 
(list 5045.415 537.9946) 
(list 5119.4375 537.6446)))
(apply 'command (append '("pline") coords '("c")))
(setq currobj (ssadd (entlast) currobj))
(setq coords (list 
(list 5119.4375 537.5016) 
(list 5045.415 537.8516) 
(list 5045.415 537.6746) 
(list 5119.4375 537.4246)))
(apply 'command (append '("pline") coords '("c")))
(setq currobj (ssadd (entlast) currobj))
(setq coords (list 
(list 5119.4375 537.2816) 
(list 5045.415 537.5316) 
(list 5045.415 537.3546) 
(list 5119.4375 537.2046)))
(apply 'command (append '("pline") coords '("c")))
(setq currobj (ssadd (entlast) currobj))
(setq coords (list 
(list 5119.4375 537.0616) 
(list 5045.415 537.2116) 
(list 5045.415 537.0346) 
(list 5119.4375 536.9846)))
(apply 'command (append '("pline") coords '("c")))
(setq currobj (ssadd (entlast) currobj))
(setq coords (list 
(list 5119.4375 536.8416) 
(list 5045.415 536.8916) 
(list 5045.415 536.7146) 
(list 5119.4375 536.7646)))
(apply 'command (append '("pline") coords '("c")))
(setq currobj (ssadd (entlast) currobj))
(setq coords (list 
(list 5119.4375 536.6216) 
(list 5045.415 536.5716) 
(list 5045.415 536.3946) 
(list 5119.4375 536.5446)))
(apply 'command (append '("pline") coords '("c")))
(setq currobj (ssadd (entlast) currobj))
(setq coords (list 
(list 5119.4375 536.4016) 
(list 5045.415 536.2516) 
(list 5045.415 536.0746) 
(list 5119.4375 536.3246)))
(apply 'command (append '("pline") coords '("c")))
(setq currobj (ssadd (entlast) currobj))
(setq coords (list 
(list 5119.4375 536.1816) 
(list 5045.415 535.9316) 
(list 5045.415 535.7546) 
(list 5119.4375 536.1046)))
(apply 'command (append '("pline") coords '("c")))
(setq currobj (ssadd (entlast) currobj))
(setq coords (list 
(list 5119.4375 535.9616) 
(list 5045.415 535.6116) 
(list 5045.415 535.4346) 
(list 5119.4375 535.8846)))
(apply 'command (append '("pline") coords '("c")))
(setq currobj (ssadd (entlast) currobj))
(setq coords (list 
(list 5119.4375 535.7416) 
(list 5045.415 535.2916) 
(list 5045.415 535.1146) 
(list 5119.4375 535.6646)))
(apply 'command (append '("pline") coords '("c")))
(setq currobj (ssadd (entlast) currobj))
(setq coords (list 
(list 5119.4375 535.5216) 
(list 5045.415 534.9716) 
(list 5045.415 534.7946) 
(list 5119.4375 535.4446)))
(apply 'command (append '("pline") coords '("c")))
(setq currobj (ssadd (entlast) currobj))
(setq coords (list 
(list 5119.4375 535.3016) 
(list 5045.415 534.6516) 
(list 5045.415 534.4746) 
(list 5119.4375 535.2246)))
(apply 'command (append '("pline") coords '("c")))
(setq currobj (ssadd (entlast) currobj))
(command "_layer" "set" "nitride" "")
(command "_layer" "set" "text" "")
(command "_circle" "5119.0625,524.0816" "0.075")
(command "_circle" "5119.0625,524.3816" "0.075")
(command "_circle" "5119.0625,524.6816" "0.075")
(command "_circle" "5119.0625,524.9816" "0.075")
(command "_circle" "5119.0625,525.2816" "0.075")
(command "_circle" "5118.7625,524.0816" "0.075")
(command "_circle" "5118.7625,524.3816" "0.075")
(command "_circle" "5118.7625,524.6816" "0.075")
(command "_circle" "5118.7625,524.9816" "0.075")
(command "_circle" "5118.7625,525.2816" "0.075")
(command "_circle" "5118.4625,524.0816" "0.075")
(command "_circle" "5118.4625,524.3816" "0.075")
(command "_circle" "5118.4625,524.6816" "0.075")
(command "_circle" "5118.4625,524.9816" "0.075")
(command "_circle" "5118.4625,525.2816" "0.075")
(command "_circle" "5118.1625,524.0816" "0.075")
(command "_circle" "5118.1625,524.3816" "0.075")
(command "_circle" "5118.1625,524.6816" "0.075")
(command "_circle" "5118.1625,524.9816" "0.075")
(command "_circle" "5118.1625,525.2816" "0.075")
(command "_circle" "5117.8625,524.0816" "0.075")
(command "_circle" "5117.8625,524.3816" "0.075")
(command "_circle" "5117.8625,524.6816" "0.075")
(command "_circle" "5117.8625,524.9816" "0.075")
(command "_circle" "5117.8625,525.2816" "0.075")
(command "_layer" "set" "nitride" "")
(setq coords (list 
(list 5120.2625 549.5246) 
(list 5120.2625 665.1693) 
(list 5119.7375 665.1693) 
(list 5119.7375 549.5246)))
(apply 'command (append '("pline") coords '("c")))
(setq currobj (ssadd (entlast) currobj))
(command "_layer" "set" "prebias" "")
(command "_rectangle" "5119.7375,549.5246" "5120.2625,665.1693")
(setq currobj (ssadd (entlast) currobj))
(command "_layer" "set" "nitride" "")
(setq coords (list 
(list 5120.2625 665.1693) 
(list 5120.5625 675.1693) 
(list 5120.5625 675.1693) 
(list 5120.5625 676.1693) 
(list 5194.585 675.4193) 
(list 5194.585 680.3623) 
(list 5120.5625 679.6123) 
(list 5120.5625 680.6123) 
(list 5120.5625 680.6123) 
(list 5120.2625 690.6123) 
(list 5119.7375 690.6123) 
(list 5119.4375 680.6123) 
(list 5119.4375 680.6123) 
(list 5119.4375 679.6123) 
(list 5045.415 680.3623) 
(list 5045.415 675.4193) 
(list 5119.4375 676.1693) 
(list 5119.4375 675.1693) 
(list 5119.4375 675.1693) 
(list 5119.7375 665.1693)))
(apply 'command (append '("pline") coords '("c")))
(setq currobj (ssadd (entlast) currobj))
(command "_layer" "set" "prebias" "")
(setq coords (list 
(list 5119.4375 665.1693) 
(list 5119.4375 676.1693) 
(list 5045.415 675.4193) 
(list 5045.415 680.3623) 
(list 5119.4375 679.6123) 
(list 5119.4375 690.6123) 
(list 5120.5625 690.6123) 
(list 5120.5625 679.6123) 
(list 5194.585 680.3623) 
(list 5194.585 675.4193) 
(list 5120.5625 676.1693) 
(list 5120.5625 665.1693)))
(apply 'command (append '("pline") coords '("c")))
(setq currobj (ssadd (entlast) currobj))
(command "_layer" "set" "nitride" "")
(command "_layer" "set" "fda1" "")
(setq coords (list 
(list 5120.5625 676.3123) 
(list 5194.585 675.5623) 
(list 5194.585 675.7393) 
(list 5120.5625 676.3893)))
(apply 'command (append '("pline") coords '("c")))
(setq currobj (ssadd (entlast) currobj))
(setq coords (list 
(list 5120.5625 676.5323) 
(list 5194.585 675.8823) 
(list 5194.585 676.0593) 
(list 5120.5625 676.6093)))
(apply 'command (append '("pline") coords '("c")))
(setq currobj (ssadd (entlast) currobj))
(setq coords (list 
(list 5120.5625 676.7523) 
(list 5194.585 676.2023) 
(list 5194.585 676.3793) 
(list 5120.5625 676.8293)))
(apply 'command (append '("pline") coords '("c")))
(setq currobj (ssadd (entlast) currobj))
(setq coords (list 
(list 5120.5625 676.9723) 
(list 5194.585 676.5223) 
(list 5194.585 676.6993) 
(list 5120.5625 677.0493)))
(apply 'command (append '("pline") coords '("c")))
(setq currobj (ssadd (entlast) currobj))
(setq coords (list 
(list 5120.5625 677.1923) 
(list 5194.585 676.8423) 
(list 5194.585 677.0193) 
(list 5120.5625 677.2693)))
(apply 'command (append '("pline") coords '("c")))
(setq currobj (ssadd (entlast) currobj))
(setq coords (list 
(list 5120.5625 677.4123) 
(list 5194.585 677.1623) 
(list 5194.585 677.3393) 
(list 5120.5625 677.4893)))
(apply 'command (append '("pline") coords '("c")))
(setq currobj (ssadd (entlast) currobj))
(setq coords (list 
(list 5120.5625 677.6323) 
(list 5194.585 677.4823) 
(list 5194.585 677.6593) 
(list 5120.5625 677.7093)))
(apply 'command (append '("pline") coords '("c")))
(setq currobj (ssadd (entlast) currobj))
(setq coords (list 
(list 5120.5625 677.8523) 
(list 5194.585 677.8023) 
(list 5194.585 677.9793) 
(list 5120.5625 677.9293)))
(apply 'command (append '("pline") coords '("c")))
(setq currobj (ssadd (entlast) currobj))
(setq coords (list 
(list 5120.5625 678.0723) 
(list 5194.585 678.1223) 
(list 5194.585 678.2993) 
(list 5120.5625 678.1493)))
(apply 'command (append '("pline") coords '("c")))
(setq currobj (ssadd (entlast) currobj))
(setq coords (list 
(list 5120.5625 678.2923) 
(list 5194.585 678.4423) 
(list 5194.585 678.6193) 
(list 5120.5625 678.3693)))
(apply 'command (append '("pline") coords '("c")))
(setq currobj (ssadd (entlast) currobj))
(setq coords (list 
(list 5120.5625 678.5123) 
(list 5194.585 678.7623) 
(list 5194.585 678.9393) 
(list 5120.5625 678.5893)))
(apply 'command (append '("pline") coords '("c")))
(setq currobj (ssadd (entlast) currobj))
(setq coords (list 
(list 5120.5625 678.7323) 
(list 5194.585 679.0823) 
(list 5194.585 679.2593) 
(list 5120.5625 678.8093)))
(apply 'command (append '("pline") coords '("c")))
(setq currobj (ssadd (entlast) currobj))
(setq coords (list 
(list 5120.5625 678.9523) 
(list 5194.585 679.4023) 
(list 5194.585 679.5793) 
(list 5120.5625 679.0293)))
(apply 'command (append '("pline") coords '("c")))
(setq currobj (ssadd (entlast) currobj))
(setq coords (list 
(list 5120.5625 679.1723) 
(list 5194.585 679.7223) 
(list 5194.585 679.8993) 
(list 5120.5625 679.2493)))
(apply 'command (append '("pline") coords '("c")))
(setq currobj (ssadd (entlast) currobj))
(setq coords (list 
(list 5120.5625 679.3923) 
(list 5194.585 680.0423) 
(list 5194.585 680.2193) 
(list 5120.5625 679.4693)))
(apply 'command (append '("pline") coords '("c")))
(setq currobj (ssadd (entlast) currobj))
(setq coords (list 
(list 5119.4375 679.4693) 
(list 5045.415 680.2193) 
(list 5045.415 680.0423) 
(list 5119.4375 679.3923)))
(apply 'command (append '("pline") coords '("c")))
(setq currobj (ssadd (entlast) currobj))
(setq coords (list 
(list 5119.4375 679.2493) 
(list 5045.415 679.8993) 
(list 5045.415 679.7223) 
(list 5119.4375 679.1723)))
(apply 'command (append '("pline") coords '("c")))
(setq currobj (ssadd (entlast) currobj))
(setq coords (list 
(list 5119.4375 679.0293) 
(list 5045.415 679.5793) 
(list 5045.415 679.4023) 
(list 5119.4375 678.9523)))
(apply 'command (append '("pline") coords '("c")))
(setq currobj (ssadd (entlast) currobj))
(setq coords (list 
(list 5119.4375 678.8093) 
(list 5045.415 679.2593) 
(list 5045.415 679.0823) 
(list 5119.4375 678.7323)))
(apply 'command (append '("pline") coords '("c")))
(setq currobj (ssadd (entlast) currobj))
(setq coords (list 
(list 5119.4375 678.5893) 
(list 5045.415 678.9393) 
(list 5045.415 678.7623) 
(list 5119.4375 678.5123)))
(apply 'command (append '("pline") coords '("c")))
(setq currobj (ssadd (entlast) currobj))
(setq coords (list 
(list 5119.4375 678.3693) 
(list 5045.415 678.6193) 
(list 5045.415 678.4423) 
(list 5119.4375 678.2923)))
(apply 'command (append '("pline") coords '("c")))
(setq currobj (ssadd (entlast) currobj))
(setq coords (list 
(list 5119.4375 678.1493) 
(list 5045.415 678.2993) 
(list 5045.415 678.1223) 
(list 5119.4375 678.0723)))
(apply 'command (append '("pline") coords '("c")))
(setq currobj (ssadd (entlast) currobj))
(setq coords (list 
(list 5119.4375 677.9293) 
(list 5045.415 677.9793) 
(list 5045.415 677.8023) 
(list 5119.4375 677.8523)))
(apply 'command (append '("pline") coords '("c")))
(setq currobj (ssadd (entlast) currobj))
(setq coords (list 
(list 5119.4375 677.7093) 
(list 5045.415 677.6593) 
(list 5045.415 677.4823) 
(list 5119.4375 677.6323)))
(apply 'command (append '("pline") coords '("c")))
(setq currobj (ssadd (entlast) currobj))
(setq coords (list 
(list 5119.4375 677.4893) 
(list 5045.415 677.3393) 
(list 5045.415 677.1623) 
(list 5119.4375 677.4123)))
(apply 'command (append '("pline") coords '("c")))
(setq currobj (ssadd (entlast) currobj))
(setq coords (list 
(list 5119.4375 677.2693) 
(list 5045.415 677.0193) 
(list 5045.415 676.8423) 
(list 5119.4375 677.1923)))
(apply 'command (append '("pline") coords '("c")))
(setq currobj (ssadd (entlast) currobj))
(setq coords (list 
(list 5119.4375 677.0493) 
(list 5045.415 676.6993) 
(list 5045.415 676.5223) 
(list 5119.4375 676.9723)))
(apply 'command (append '("pline") coords '("c")))
(setq currobj (ssadd (entlast) currobj))
(setq coords (list 
(list 5119.4375 676.8293) 
(list 5045.415 676.3793) 
(list 5045.415 676.2023) 
(list 5119.4375 676.7523)))
(apply 'command (append '("pline") coords '("c")))
(setq currobj (ssadd (entlast) currobj))
(setq coords (list 
(list 5119.4375 676.6093) 
(list 5045.415 676.0593) 
(list 5045.415 675.8823) 
(list 5119.4375 676.5323)))
(apply 'command (append '("pline") coords '("c")))
(setq currobj (ssadd (entlast) currobj))
(setq coords (list 
(list 5119.4375 676.3893) 
(list 5045.415 675.7393) 
(list 5045.415 675.5623) 
(list 5119.4375 676.3123)))
(apply 'command (append '("pline") coords '("c")))
(setq currobj (ssadd (entlast) currobj))
(command "_layer" "set" "nitride" "")
(command "_layer" "set" "text" "")
(command "_circle" "5119.0625,665.1693" "0.075")
(command "_circle" "5119.0625,665.4693" "0.075")
(command "_circle" "5119.0625,665.7693" "0.075")
(command "_circle" "5119.0625,666.0693" "0.075")
(command "_circle" "5119.0625,666.3693" "0.075")
(command "_circle" "5118.7625,665.1693" "0.075")
(command "_circle" "5118.7625,665.4693" "0.075")
(command "_circle" "5118.7625,665.7693" "0.075")
(command "_circle" "5118.7625,666.0693" "0.075")
(command "_circle" "5118.7625,666.3693" "0.075")
(command "_circle" "5118.4625,665.1693" "0.075")
(command "_circle" "5118.4625,665.4693" "0.075")
(command "_circle" "5118.4625,665.7693" "0.075")
(command "_circle" "5118.4625,666.0693" "0.075")
(command "_circle" "5118.4625,666.3693" "0.075")
(command "_circle" "5118.1625,665.1693" "0.075")
(command "_circle" "5118.1625,665.4693" "0.075")
(command "_circle" "5118.1625,665.7693" "0.075")
(command "_circle" "5118.1625,666.0693" "0.075")
(command "_circle" "5118.1625,666.3693" "0.075")
(command "_circle" "5117.8625,665.1693" "0.075")
(command "_circle" "5117.8625,665.4693" "0.075")
(command "_circle" "5117.8625,665.7693" "0.075")
(command "_circle" "5117.8625,666.0693" "0.075")
(command "_circle" "5117.8625,666.3693" "0.075")
(command "_layer" "set" "nitride" "")
(setq coords (list 
(list 5120.2625 690.6123) 
(list 5120.2625 806.257) 
(list 5119.7375 806.257) 
(list 5119.7375 690.6123)))
(apply 'command (append '("pline") coords '("c")))
(setq currobj (ssadd (entlast) currobj))
(command "_layer" "set" "prebias" "")
(command "_rectangle" "5119.7375,690.6123" "5120.2625,806.257")
(setq currobj (ssadd (entlast) currobj))
(command "_layer" "set" "nitride" "")
(setq coords (list 
(list 5120.2625 806.257) 
(list 5120.5625 816.257) 
(list 5120.5625 816.257) 
(list 5120.5625 817.257) 
(list 5194.585 816.507) 
(list 5194.585 821.45) 
(list 5120.5625 820.7) 
(list 5120.5625 821.7) 
(list 5120.5625 821.7) 
(list 5120.2625 831.7) 
(list 5119.7375 831.7) 
(list 5119.4375 821.7) 
(list 5119.4375 821.7) 
(list 5119.4375 820.7) 
(list 5045.415 821.45) 
(list 5045.415 816.507) 
(list 5119.4375 817.257) 
(list 5119.4375 816.257) 
(list 5119.4375 816.257) 
(list 5119.7375 806.257)))
(apply 'command (append '("pline") coords '("c")))
(setq currobj (ssadd (entlast) currobj))
(command "_layer" "set" "prebias" "")
(setq coords (list 
(list 5119.4375 806.257) 
(list 5119.4375 817.257) 
(list 5045.415 816.507) 
(list 5045.415 821.45) 
(list 5119.4375 820.7) 
(list 5119.4375 831.7) 
(list 5120.5625 831.7) 
(list 5120.5625 820.7) 
(list 5194.585 821.45) 
(list 5194.585 816.507) 
(list 5120.5625 817.257) 
(list 5120.5625 806.257)))
(apply 'command (append '("pline") coords '("c")))
(setq currobj (ssadd (entlast) currobj))
(command "_layer" "set" "nitride" "")
(command "_layer" "set" "fda1" "")
(setq coords (list 
(list 5120.5625 817.4) 
(list 5194.585 816.65) 
(list 5194.585 816.827) 
(list 5120.5625 817.477)))
(apply 'command (append '("pline") coords '("c")))
(setq currobj (ssadd (entlast) currobj))
(setq coords (list 
(list 5120.5625 817.62) 
(list 5194.585 816.97) 
(list 5194.585 817.147) 
(list 5120.5625 817.697)))
(apply 'command (append '("pline") coords '("c")))
(setq currobj (ssadd (entlast) currobj))
(setq coords (list 
(list 5120.5625 817.84) 
(list 5194.585 817.29) 
(list 5194.585 817.467) 
(list 5120.5625 817.917)))
(apply 'command (append '("pline") coords '("c")))
(setq currobj (ssadd (entlast) currobj))
(setq coords (list 
(list 5120.5625 818.06) 
(list 5194.585 817.61) 
(list 5194.585 817.787) 
(list 5120.5625 818.137)))
(apply 'command (append '("pline") coords '("c")))
(setq currobj (ssadd (entlast) currobj))
(setq coords (list 
(list 5120.5625 818.28) 
(list 5194.585 817.93) 
(list 5194.585 818.107) 
(list 5120.5625 818.357)))
(apply 'command (append '("pline") coords '("c")))
(setq currobj (ssadd (entlast) currobj))
(setq coords (list 
(list 5120.5625 818.5) 
(list 5194.585 818.25) 
(list 5194.585 818.427) 
(list 5120.5625 818.577)))
(apply 'command (append '("pline") coords '("c")))
(setq currobj (ssadd (entlast) currobj))
(setq coords (list 
(list 5120.5625 818.72) 
(list 5194.585 818.57) 
(list 5194.585 818.747) 
(list 5120.5625 818.797)))
(apply 'command (append '("pline") coords '("c")))
(setq currobj (ssadd (entlast) currobj))
(setq coords (list 
(list 5120.5625 818.94) 
(list 5194.585 818.89) 
(list 5194.585 819.067) 
(list 5120.5625 819.017)))
(apply 'command (append '("pline") coords '("c")))
(setq currobj (ssadd (entlast) currobj))
(setq coords (list 
(list 5120.5625 819.16) 
(list 5194.585 819.21) 
(list 5194.585 819.387) 
(list 5120.5625 819.237)))
(apply 'command (append '("pline") coords '("c")))
(setq currobj (ssadd (entlast) currobj))
(setq coords (list 
(list 5120.5625 819.38) 
(list 5194.585 819.53) 
(list 5194.585 819.707) 
(list 5120.5625 819.457)))
(apply 'command (append '("pline") coords '("c")))
(setq currobj (ssadd (entlast) currobj))
(setq coords (list 
(list 5120.5625 819.6) 
(list 5194.585 819.85) 
(list 5194.585 820.027) 
(list 5120.5625 819.677)))
(apply 'command (append '("pline") coords '("c")))
(setq currobj (ssadd (entlast) currobj))
(setq coords (list 
(list 5120.5625 819.82) 
(list 5194.585 820.17) 
(list 5194.585 820.347) 
(list 5120.5625 819.897)))
(apply 'command (append '("pline") coords '("c")))
(setq currobj (ssadd (entlast) currobj))
(setq coords (list 
(list 5120.5625 820.04) 
(list 5194.585 820.49) 
(list 5194.585 820.667) 
(list 5120.5625 820.117)))
(apply 'command (append '("pline") coords '("c")))
(setq currobj (ssadd (entlast) currobj))
(setq coords (list 
(list 5120.5625 820.26) 
(list 5194.585 820.81) 
(list 5194.585 820.987) 
(list 5120.5625 820.337)))
(apply 'command (append '("pline") coords '("c")))
(setq currobj (ssadd (entlast) currobj))
(setq coords (list 
(list 5120.5625 820.48) 
(list 5194.585 821.13) 
(list 5194.585 821.307) 
(list 5120.5625 820.557)))
(apply 'command (append '("pline") coords '("c")))
(setq currobj (ssadd (entlast) currobj))
(setq coords (list 
(list 5119.4375 820.557) 
(list 5045.415 821.307) 
(list 5045.415 821.13) 
(list 5119.4375 820.48)))
(apply 'command (append '("pline") coords '("c")))
(setq currobj (ssadd (entlast) currobj))
(setq coords (list 
(list 5119.4375 820.337) 
(list 5045.415 820.987) 
(list 5045.415 820.81) 
(list 5119.4375 820.26)))
(apply 'command (append '("pline") coords '("c")))
(setq currobj (ssadd (entlast) currobj))
(setq coords (list 
(list 5119.4375 820.117) 
(list 5045.415 820.667) 
(list 5045.415 820.49) 
(list 5119.4375 820.04)))
(apply 'command (append '("pline") coords '("c")))
(setq currobj (ssadd (entlast) currobj))
(setq coords (list 
(list 5119.4375 819.897) 
(list 5045.415 820.347) 
(list 5045.415 820.17) 
(list 5119.4375 819.82)))
(apply 'command (append '("pline") coords '("c")))
(setq currobj (ssadd (entlast) currobj))
(setq coords (list 
(list 5119.4375 819.677) 
(list 5045.415 820.027) 
(list 5045.415 819.85) 
(list 5119.4375 819.6)))
(apply 'command (append '("pline") coords '("c")))
(setq currobj (ssadd (entlast) currobj))
(setq coords (list 
(list 5119.4375 819.457) 
(list 5045.415 819.707) 
(list 5045.415 819.53) 
(list 5119.4375 819.38)))
(apply 'command (append '("pline") coords '("c")))
(setq currobj (ssadd (entlast) currobj))
(setq coords (list 
(list 5119.4375 819.237) 
(list 5045.415 819.387) 
(list 5045.415 819.21) 
(list 5119.4375 819.16)))
(apply 'command (append '("pline") coords '("c")))
(setq currobj (ssadd (entlast) currobj))
(setq coords (list 
(list 5119.4375 819.017) 
(list 5045.415 819.067) 
(list 5045.415 818.89) 
(list 5119.4375 818.94)))
(apply 'command (append '("pline") coords '("c")))
(setq currobj (ssadd (entlast) currobj))
(setq coords (list 
(list 5119.4375 818.797) 
(list 5045.415 818.747) 
(list 5045.415 818.57) 
(list 5119.4375 818.72)))
(apply 'command (append '("pline") coords '("c")))
(setq currobj (ssadd (entlast) currobj))
(setq coords (list 
(list 5119.4375 818.577) 
(list 5045.415 818.427) 
(list 5045.415 818.25) 
(list 5119.4375 818.5)))
(apply 'command (append '("pline") coords '("c")))
(setq currobj (ssadd (entlast) currobj))
(setq coords (list 
(list 5119.4375 818.357) 
(list 5045.415 818.107) 
(list 5045.415 817.93) 
(list 5119.4375 818.28)))
(apply 'command (append '("pline") coords '("c")))
(setq currobj (ssadd (entlast) currobj))
(setq coords (list 
(list 5119.4375 818.137) 
(list 5045.415 817.787) 
(list 5045.415 817.61) 
(list 5119.4375 818.06)))
(apply 'command (append '("pline") coords '("c")))
(setq currobj (ssadd (entlast) currobj))
(setq coords (list 
(list 5119.4375 817.917) 
(list 5045.415 817.467) 
(list 5045.415 817.29) 
(list 5119.4375 817.84)))
(apply 'command (append '("pline") coords '("c")))
(setq currobj (ssadd (entlast) currobj))
(setq coords (list 
(list 5119.4375 817.697) 
(list 5045.415 817.147) 
(list 5045.415 816.97) 
(list 5119.4375 817.62)))
(apply 'command (append '("pline") coords '("c")))
(setq currobj (ssadd (entlast) currobj))
(setq coords (list 
(list 5119.4375 817.477) 
(list 5045.415 816.827) 
(list 5045.415 816.65) 
(list 5119.4375 817.4)))
(apply 'command (append '("pline") coords '("c")))
(setq currobj (ssadd (entlast) currobj))
(command "_layer" "set" "nitride" "")
(command "_layer" "set" "text" "")
(command "_circle" "5119.0625,806.257" "0.075")
(command "_circle" "5119.0625,806.557" "0.075")
(command "_circle" "5119.0625,806.857" "0.075")
(command "_circle" "5119.0625,807.157" "0.075")
(command "_circle" "5119.0625,807.457" "0.075")
(command "_circle" "5118.7625,806.257" "0.075")
(command "_circle" "5118.7625,806.557" "0.075")
(command "_circle" "5118.7625,806.857" "0.075")
(command "_circle" "5118.7625,807.157" "0.075")
(command "_circle" "5118.7625,807.457" "0.075")
(command "_circle" "5118.4625,806.257" "0.075")
(command "_circle" "5118.4625,806.557" "0.075")
(command "_circle" "5118.4625,806.857" "0.075")
(command "_circle" "5118.4625,807.157" "0.075")
(command "_circle" "5118.4625,807.457" "0.075")
(command "_circle" "5118.1625,806.257" "0.075")
(command "_circle" "5118.1625,806.557" "0.075")
(command "_circle" "5118.1625,806.857" "0.075")
(command "_circle" "5118.1625,807.157" "0.075")
(command "_circle" "5118.1625,807.457" "0.075")
(command "_circle" "5117.8625,806.257" "0.075")
(command "_circle" "5117.8625,806.557" "0.075")
(command "_circle" "5117.8625,806.857" "0.075")
(command "_circle" "5117.8625,807.157" "0.075")
(command "_circle" "5117.8625,807.457" "0.075")
(command "_layer" "set" "nitride" "")
(setq coords (list 
(list 5120.2625 831.7) 
(list 5120.2625 836.7) 
(list 5119.7375 836.7) 
(list 5119.7375 831.7)))
(apply 'command (append '("pline") coords '("c")))
(setq currobj (ssadd (entlast) currobj))
(command "_layer" "set" "prebias" "")
(command "_rectangle" "5119.7375,831.7" "5120.2625,836.7")
(setq currobj (ssadd (entlast) currobj))
(command "_layer" "set" "nitride" "")
(setq cooledsinglenanobeam16 currobj)
(setq currobj nil)
(setq currobj (ssadd))
; DRAWING PHOTONIC CRYSTAL
(command "_layer" "set" "negYjunc" "")
(setq coords (list 
(list 5120.135 866.7) 
(list 5120 851.7) 
(list 5120 866.7)))
(apply 'command (append '("pline") coords '("c")))
(setq currobj (ssadd (entlast) currobj))
(setq coords (list 
(list 5120.2625 836.7) 
(list 5120.415 866.7) 
(list 5121.137 866.7) 
(list 5121.137 836.7)))
(apply 'command (append '("pline") coords '("c")))
(setq currobj (ssadd (entlast) currobj))
(setq coords (list 
(list 5119.865 866.7) 
(list 5120 851.7) 
(list 5120 866.7)))
(apply 'command (append '("pline") coords '("c")))
(setq currobj (ssadd (entlast) currobj))
(setq coords (list 
(list 5119.7375 836.7) 
(list 5119.585 866.7) 
(list 5118.863 866.7) 
(list 5118.863 836.7)))
(apply 'command (append '("pline") coords '("c")))
(setq currobj (ssadd (entlast) currobj))
(command "_layer" "set" "nitride" "")
(setq yjunction16 currobj)
(setq currobj nil)
(setq currobj (ssadd))
(setq tap16 nil)
(setq tap16 (ssadd))
(command "_layer" "set" "phc" "")
(setq coords (list 
(list 5120 866.7) 
(list 5120.135 866.7) 
(list 5120.135 866.7103) 
(list 5120.135 866.7206) 
(list 5120.135 866.7308) 
(list 5120.135 866.7411) 
(list 5120.135 866.7514) 
(list 5120.135 866.7617) 
(list 5120.135 866.7719) 
(list 5120.135 866.7822) 
(list 5120.135 866.7925) 
(list 5120.135 866.8028) 
(list 5120.135 866.8131) 
(list 5120.135 866.8233) 
(list 5120.135 866.8336) 
(list 5120.135 866.8439) 
(list 5120.135 866.8542) 
(list 5120.135 866.8644) 
(list 5120.135 866.8747) 
(list 5120.135 866.885) 
(list 5120.135 866.8953) 
(list 5120.135 866.9056) 
(list 5120.135 866.9158) 
(list 5120.135 866.9261) 
(list 5120.135 866.9364) 
(list 5120.135 866.9467) 
(list 5120.135 866.9569) 
(list 5120.135 866.9672) 
(list 5120.135 866.9775) 
(list 5120.135 866.9878) 
(list 5120.135 866.9981) 
(list 5120.135 867.0083) 
(list 5120.135 867.0186) 
(list 5120.135 867.0289) 
(list 5120.135 867.0392) 
(list 5120.135 867.0494) 
(list 5120.135 867.0597) 
(list 5120.135 867.07) 
(list 5120 867.07)))
(apply 'command (append '("pline") coords '("c")))
(setq tap16 (ssadd (entlast) tap16))
(command "_mirror" (entlast) "" "5120,900" "5120,901" "No")
(setq tap16 (ssadd (entlast) tap16))
(setq coords (list 
(list 5120.4252 866.7) 
(list 5120.415 866.7) 
(list 5120.4153 866.7103) 
(list 5120.4155 866.7206) 
(list 5120.4158 866.7308) 
(list 5120.4159 866.7411) 
(list 5120.416 866.7514) 
(list 5120.416 866.7617) 
(list 5120.4158 866.7719) 
(list 5120.4156 866.7822) 
(list 5120.4153 866.7925) 
(list 5120.4149 866.8028) 
(list 5120.4144 866.8131) 
(list 5120.4139 866.8233) 
(list 5120.4133 866.8336) 
(list 5120.4128 866.8439) 
(list 5120.4122 866.8542) 
(list 5120.4118 866.8644) 
(list 5120.4114 866.8747) 
(list 5120.4111 866.885) 
(list 5120.4109 866.8953) 
(list 5120.411 866.9056) 
(list 5120.4111 866.9158) 
(list 5120.4115 866.9261) 
(list 5120.4121 866.9364) 
(list 5120.4128 866.9467) 
(list 5120.4137 866.9569) 
(list 5120.4147 866.9672) 
(list 5120.4159 866.9775) 
(list 5120.4172 866.9878) 
(list 5120.4185 866.9981) 
(list 5120.4198 867.0083) 
(list 5120.421 867.0186) 
(list 5120.4222 867.0289) 
(list 5120.4233 867.0392) 
(list 5120.4241 867.0494) 
(list 5120.4248 867.0597) 
(list 5120.4252 867.07) 
(list 5120.4252 867.07)))
(apply 'command (append '("pline") coords '("c")))
(setq tap16 (ssadd (entlast) tap16))
(command "_mirror" (entlast) "" "5120,900" "5120,901" "No")
(setq tap16 (ssadd (entlast) tap16))
(setq coords (list 
(list 5121.137 866.7) 
(list 5120.4252 866.7) 
(list 5120.4252 866.7103) 
(list 5120.4252 866.7206) 
(list 5120.4252 866.7308) 
(list 5120.4252 866.7411) 
(list 5120.4252 866.7514) 
(list 5120.4252 866.7617) 
(list 5120.4252 866.7719) 
(list 5120.4252 866.7822) 
(list 5120.4252 866.7925) 
(list 5120.4252 866.8028) 
(list 5120.4252 866.8131) 
(list 5120.4252 866.8233) 
(list 5120.4252 866.8336) 
(list 5120.4252 866.8439) 
(list 5120.4252 866.8542) 
(list 5120.4252 866.8644) 
(list 5120.4252 866.8747) 
(list 5120.4252 866.885) 
(list 5120.4252 866.8953) 
(list 5120.4252 866.9056) 
(list 5120.4252 866.9158) 
(list 5120.4252 866.9261) 
(list 5120.4252 866.9364) 
(list 5120.4252 866.9467) 
(list 5120.4252 866.9569) 
(list 5120.4252 866.9672) 
(list 5120.4252 866.9775) 
(list 5120.4252 866.9878) 
(list 5120.4252 866.9981) 
(list 5120.4252 867.0083) 
(list 5120.4252 867.0186) 
(list 5120.4252 867.0289) 
(list 5120.4252 867.0392) 
(list 5120.4252 867.0494) 
(list 5120.4252 867.0597) 
(list 5120.4252 867.07) 
(list 5121.137 867.07)))
(apply 'command (append '("pline") coords '("c")))
(setq tap16 (ssadd (entlast) tap16))
(command "_mirror" (entlast) "" "5120,900" "5120,901" "No")
(setq tap16 (ssadd (entlast) tap16))
(setq coords (list 
(list 5120 867.07) 
(list 5120.135 867.07) 
(list 5120.135 867.0803) 
(list 5120.135 867.0906) 
(list 5120.135 867.1008) 
(list 5120.135 867.1111) 
(list 5120.135 867.1214) 
(list 5120.135 867.1317) 
(list 5120.135 867.1419) 
(list 5120.135 867.1522) 
(list 5120.135 867.1625) 
(list 5120.135 867.1728) 
(list 5120.135 867.1831) 
(list 5120.135 867.1933) 
(list 5120.135 867.2036) 
(list 5120.135 867.2139) 
(list 5120.135 867.2242) 
(list 5120.135 867.2344) 
(list 5120.135 867.2447) 
(list 5120.135 867.255) 
(list 5120.135 867.2653) 
(list 5120.135 867.2756) 
(list 5120.135 867.2858) 
(list 5120.135 867.2961) 
(list 5120.135 867.3064) 
(list 5120.135 867.3167) 
(list 5120.135 867.3269) 
(list 5120.135 867.3372) 
(list 5120.135 867.3475) 
(list 5120.135 867.3578) 
(list 5120.135 867.3681) 
(list 5120.135 867.3783) 
(list 5120.135 867.3886) 
(list 5120.135 867.3989) 
(list 5120.135 867.4092) 
(list 5120.135 867.4194) 
(list 5120.135 867.4297) 
(list 5120.135 867.44) 
(list 5120 867.44)))
(apply 'command (append '("pline") coords '("c")))
(setq tap16 (ssadd (entlast) tap16))
(command "_mirror" (entlast) "" "5120,900" "5120,901" "No")
(setq tap16 (ssadd (entlast) tap16))
(setq coords (list 
(list 5120.4355 867.07) 
(list 5120.4252 867.07) 
(list 5120.4254 867.0803) 
(list 5120.4252 867.0906) 
(list 5120.4248 867.1008) 
(list 5120.424 867.1111) 
(list 5120.423 867.1214) 
(list 5120.4217 867.1317) 
(list 5120.4201 867.1419) 
(list 5120.4184 867.1522) 
(list 5120.4165 867.1625) 
(list 5120.4145 867.1728) 
(list 5120.4125 867.1831) 
(list 5120.4106 867.1933) 
(list 5120.4087 867.2036) 
(list 5120.4071 867.2139) 
(list 5120.4056 867.2242) 
(list 5120.4045 867.2344) 
(list 5120.4037 867.2447) 
(list 5120.4033 867.255) 
(list 5120.4032 867.2653) 
(list 5120.4037 867.2756) 
(list 5120.4045 867.2858) 
(list 5120.4058 867.2961) 
(list 5120.4074 867.3064) 
(list 5120.4095 867.3167) 
(list 5120.4118 867.3269) 
(list 5120.4144 867.3372) 
(list 5120.4171 867.3475) 
(list 5120.4199 867.3578) 
(list 5120.4227 867.3681) 
(list 5120.4255 867.3783) 
(list 5120.428 867.3886) 
(list 5120.4303 867.3989) 
(list 5120.4323 867.4092) 
(list 5120.4338 867.4194) 
(list 5120.4349 867.4297) 
(list 5120.4355 867.44) 
(list 5120.4355 867.44)))
(apply 'command (append '("pline") coords '("c")))
(setq tap16 (ssadd (entlast) tap16))
(command "_mirror" (entlast) "" "5120,900" "5120,901" "No")
(setq tap16 (ssadd (entlast) tap16))
(setq coords (list 
(list 5121.137 867.07) 
(list 5120.4355 867.07) 
(list 5120.4355 867.0803) 
(list 5120.4355 867.0906) 
(list 5120.4355 867.1008) 
(list 5120.4355 867.1111) 
(list 5120.4355 867.1214) 
(list 5120.4355 867.1317) 
(list 5120.4355 867.1419) 
(list 5120.4355 867.1522) 
(list 5120.4355 867.1625) 
(list 5120.4355 867.1728) 
(list 5120.4355 867.1831) 
(list 5120.4355 867.1933) 
(list 5120.4355 867.2036) 
(list 5120.4355 867.2139) 
(list 5120.4355 867.2242) 
(list 5120.4355 867.2344) 
(list 5120.4355 867.2447) 
(list 5120.4355 867.255) 
(list 5120.4355 867.2653) 
(list 5120.4355 867.2756) 
(list 5120.4355 867.2858) 
(list 5120.4355 867.2961) 
(list 5120.4355 867.3064) 
(list 5120.4355 867.3167) 
(list 5120.4355 867.3269) 
(list 5120.4355 867.3372) 
(list 5120.4355 867.3475) 
(list 5120.4355 867.3578) 
(list 5120.4355 867.3681) 
(list 5120.4355 867.3783) 
(list 5120.4355 867.3886) 
(list 5120.4355 867.3989) 
(list 5120.4355 867.4092) 
(list 5120.4355 867.4194) 
(list 5120.4355 867.4297) 
(list 5120.4355 867.44) 
(list 5121.137 867.44)))
(apply 'command (append '("pline") coords '("c")))
(setq tap16 (ssadd (entlast) tap16))
(command "_mirror" (entlast) "" "5120,900" "5120,901" "No")
(setq tap16 (ssadd (entlast) tap16))
(setq coords (list 
(list 5120 867.44) 
(list 5120.135 867.44) 
(list 5120.135 867.4503) 
(list 5120.135 867.4606) 
(list 5120.135 867.4708) 
(list 5120.135 867.4811) 
(list 5120.135 867.4914) 
(list 5120.135 867.5017) 
(list 5120.135 867.5119) 
(list 5120.135 867.5222) 
(list 5120.135 867.5325) 
(list 5120.135 867.5428) 
(list 5120.135 867.5531) 
(list 5120.135 867.5633) 
(list 5120.135 867.5736) 
(list 5120.135 867.5839) 
(list 5120.135 867.5942) 
(list 5120.135 867.6044) 
(list 5120.135 867.6147) 
(list 5120.135 867.625) 
(list 5120.135 867.6353) 
(list 5120.135 867.6456) 
(list 5120.135 867.6558) 
(list 5120.135 867.6661) 
(list 5120.135 867.6764) 
(list 5120.135 867.6867) 
(list 5120.135 867.6969) 
(list 5120.135 867.7072) 
(list 5120.135 867.7175) 
(list 5120.135 867.7278) 
(list 5120.135 867.7381) 
(list 5120.135 867.7483) 
(list 5120.135 867.7586) 
(list 5120.135 867.7689) 
(list 5120.135 867.7792) 
(list 5120.135 867.7894) 
(list 5120.135 867.7997) 
(list 5120.135 867.81) 
(list 5120 867.81)))
(apply 'command (append '("pline") coords '("c")))
(setq tap16 (ssadd (entlast) tap16))
(command "_mirror" (entlast) "" "5120,900" "5120,901" "No")
(setq tap16 (ssadd (entlast) tap16))
(setq coords (list 
(list 5120.4457 867.44) 
(list 5120.4355 867.44) 
(list 5120.4355 867.4503) 
(list 5120.4349 867.4606) 
(list 5120.4338 867.4708) 
(list 5120.4321 867.4811) 
(list 5120.43 867.4914) 
(list 5120.4274 867.5017) 
(list 5120.4244 867.5119) 
(list 5120.4212 867.5222) 
(list 5120.4177 867.5325) 
(list 5120.4142 867.5428) 
(list 5120.4106 867.5531) 
(list 5120.4073 867.5633) 
(list 5120.4041 867.5736) 
(list 5120.4013 867.5839) 
(list 5120.399 867.5942) 
(list 5120.3972 867.6044) 
(list 5120.396 867.6147) 
(list 5120.3954 867.625) 
(list 5120.3955 867.6353) 
(list 5120.3964 867.6456) 
(list 5120.3979 867.6558) 
(list 5120.4001 867.6661) 
(list 5120.4028 867.6764) 
(list 5120.4062 867.6867) 
(list 5120.4099 867.6969) 
(list 5120.414 867.7072) 
(list 5120.4183 867.7175) 
(list 5120.4227 867.7278) 
(list 5120.427 867.7381) 
(list 5120.4312 867.7483) 
(list 5120.435 867.7586) 
(list 5120.4385 867.7689) 
(list 5120.4413 867.7792) 
(list 5120.4435 867.7894) 
(list 5120.445 867.7997) 
(list 5120.4457 867.81) 
(list 5120.4457 867.81)))
(apply 'command (append '("pline") coords '("c")))
(setq tap16 (ssadd (entlast) tap16))
(command "_mirror" (entlast) "" "5120,900" "5120,901" "No")
(setq tap16 (ssadd (entlast) tap16))
(setq coords (list 
(list 5121.137 867.44) 
(list 5120.4457 867.44) 
(list 5120.4457 867.4503) 
(list 5120.4457 867.4606) 
(list 5120.4457 867.4708) 
(list 5120.4457 867.4811) 
(list 5120.4457 867.4914) 
(list 5120.4457 867.5017) 
(list 5120.4457 867.5119) 
(list 5120.4457 867.5222) 
(list 5120.4457 867.5325) 
(list 5120.4457 867.5428) 
(list 5120.4457 867.5531) 
(list 5120.4457 867.5633) 
(list 5120.4457 867.5736) 
(list 5120.4457 867.5839) 
(list 5120.4457 867.5942) 
(list 5120.4457 867.6044) 
(list 5120.4457 867.6147) 
(list 5120.4457 867.625) 
(list 5120.4457 867.6353) 
(list 5120.4457 867.6456) 
(list 5120.4457 867.6558) 
(list 5120.4457 867.6661) 
(list 5120.4457 867.6764) 
(list 5120.4457 867.6867) 
(list 5120.4457 867.6969) 
(list 5120.4457 867.7072) 
(list 5120.4457 867.7175) 
(list 5120.4457 867.7278) 
(list 5120.4457 867.7381) 
(list 5120.4457 867.7483) 
(list 5120.4457 867.7586) 
(list 5120.4457 867.7689) 
(list 5120.4457 867.7792) 
(list 5120.4457 867.7894) 
(list 5120.4457 867.7997) 
(list 5120.4457 867.81) 
(list 5121.137 867.81)))
(apply 'command (append '("pline") coords '("c")))
(setq tap16 (ssadd (entlast) tap16))
(command "_mirror" (entlast) "" "5120,900" "5120,901" "No")
(setq tap16 (ssadd (entlast) tap16))
(setq coords (list 
(list 5120 867.81) 
(list 5120.135 867.81) 
(list 5120.135 867.8203) 
(list 5120.135 867.8306) 
(list 5120.135 867.8408) 
(list 5120.135 867.8511) 
(list 5120.135 867.8614) 
(list 5120.135 867.8717) 
(list 5120.135 867.8819) 
(list 5120.135 867.8922) 
(list 5120.135 867.9025) 
(list 5120.135 867.9128) 
(list 5120.135 867.9231) 
(list 5120.135 867.9333) 
(list 5120.135 867.9436) 
(list 5120.135 867.9539) 
(list 5120.135 867.9642) 
(list 5120.135 867.9744) 
(list 5120.135 867.9847) 
(list 5120.135 867.995) 
(list 5120.135 868.0053) 
(list 5120.135 868.0156) 
(list 5120.135 868.0258) 
(list 5120.135 868.0361) 
(list 5120.135 868.0464) 
(list 5120.135 868.0567) 
(list 5120.135 868.0669) 
(list 5120.135 868.0772) 
(list 5120.135 868.0875) 
(list 5120.135 868.0978) 
(list 5120.135 868.1081) 
(list 5120.135 868.1183) 
(list 5120.135 868.1286) 
(list 5120.135 868.1389) 
(list 5120.135 868.1492) 
(list 5120.135 868.1594) 
(list 5120.135 868.1697) 
(list 5120.135 868.18) 
(list 5120 868.18)))
(apply 'command (append '("pline") coords '("c")))
(setq tap16 (ssadd (entlast) tap16))
(command "_mirror" (entlast) "" "5120,900" "5120,901" "No")
(setq tap16 (ssadd (entlast) tap16))
(setq coords (list 
(list 5120.4559 867.81) 
(list 5120.4457 867.81) 
(list 5120.4456 867.8203) 
(list 5120.4446 867.8306) 
(list 5120.4428 867.8408) 
(list 5120.4403 867.8511) 
(list 5120.437 867.8614) 
(list 5120.4331 867.8717) 
(list 5120.4287 867.8819) 
(list 5120.4239 867.8922) 
(list 5120.4189 867.9025) 
(list 5120.4138 867.9128) 
(list 5120.4088 867.9231) 
(list 5120.4039 867.9333) 
(list 5120.3995 867.9436) 
(list 5120.3956 867.9539) 
(list 5120.3924 867.9642) 
(list 5120.3899 867.9744) 
(list 5120.3883 867.9847) 
(list 5120.3876 867.995) 
(list 5120.3879 868.0053) 
(list 5120.3891 868.0156) 
(list 5120.3913 868.0258) 
(list 5120.3943 868.0361) 
(list 5120.3982 868.0464) 
(list 5120.4028 868.0567) 
(list 5120.408 868.0669) 
(list 5120.4136 868.0772) 
(list 5120.4195 868.0875) 
(list 5120.4255 868.0978) 
(list 5120.4313 868.1081) 
(list 5120.4369 868.1183) 
(list 5120.4421 868.1286) 
(list 5120.4466 868.1389) 
(list 5120.4503 868.1492) 
(list 5120.4532 868.1594) 
(list 5120.4551 868.1697) 
(list 5120.4559 868.18) 
(list 5120.4559 868.18)))
(apply 'command (append '("pline") coords '("c")))
(setq tap16 (ssadd (entlast) tap16))
(command "_mirror" (entlast) "" "5120,900" "5120,901" "No")
(setq tap16 (ssadd (entlast) tap16))
(setq coords (list 
(list 5121.137 867.81) 
(list 5120.4559 867.81) 
(list 5120.4559 867.8203) 
(list 5120.4559 867.8306) 
(list 5120.4559 867.8408) 
(list 5120.4559 867.8511) 
(list 5120.4559 867.8614) 
(list 5120.4559 867.8717) 
(list 5120.4559 867.8819) 
(list 5120.4559 867.8922) 
(list 5120.4559 867.9025) 
(list 5120.4559 867.9128) 
(list 5120.4559 867.9231) 
(list 5120.4559 867.9333) 
(list 5120.4559 867.9436) 
(list 5120.4559 867.9539) 
(list 5120.4559 867.9642) 
(list 5120.4559 867.9744) 
(list 5120.4559 867.9847) 
(list 5120.4559 867.995) 
(list 5120.4559 868.0053) 
(list 5120.4559 868.0156) 
(list 5120.4559 868.0258) 
(list 5120.4559 868.0361) 
(list 5120.4559 868.0464) 
(list 5120.4559 868.0567) 
(list 5120.4559 868.0669) 
(list 5120.4559 868.0772) 
(list 5120.4559 868.0875) 
(list 5120.4559 868.0978) 
(list 5120.4559 868.1081) 
(list 5120.4559 868.1183) 
(list 5120.4559 868.1286) 
(list 5120.4559 868.1389) 
(list 5120.4559 868.1492) 
(list 5120.4559 868.1594) 
(list 5120.4559 868.1697) 
(list 5120.4559 868.18) 
(list 5121.137 868.18)))
(apply 'command (append '("pline") coords '("c")))
(setq tap16 (ssadd (entlast) tap16))
(command "_mirror" (entlast) "" "5120,900" "5120,901" "No")
(setq tap16 (ssadd (entlast) tap16))
(setq coords (list 
(list 5120 868.18) 
(list 5120.135 868.18) 
(list 5120.135 868.1903) 
(list 5120.135 868.2006) 
(list 5120.135 868.2108) 
(list 5120.135 868.2211) 
(list 5120.135 868.2314) 
(list 5120.135 868.2417) 
(list 5120.135 868.2519) 
(list 5120.135 868.2622) 
(list 5120.135 868.2725) 
(list 5120.135 868.2828) 
(list 5120.135 868.2931) 
(list 5120.135 868.3033) 
(list 5120.135 868.3136) 
(list 5120.135 868.3239) 
(list 5120.135 868.3342) 
(list 5120.135 868.3444) 
(list 5120.135 868.3547) 
(list 5120.135 868.365) 
(list 5120.135 868.3753) 
(list 5120.135 868.3856) 
(list 5120.135 868.3958) 
(list 5120.135 868.4061) 
(list 5120.135 868.4164) 
(list 5120.135 868.4267) 
(list 5120.135 868.4369) 
(list 5120.135 868.4472) 
(list 5120.135 868.4575) 
(list 5120.135 868.4678) 
(list 5120.135 868.4781) 
(list 5120.135 868.4883) 
(list 5120.135 868.4986) 
(list 5120.135 868.5089) 
(list 5120.135 868.5192) 
(list 5120.135 868.5294) 
(list 5120.135 868.5397) 
(list 5120.135 868.55) 
(list 5120 868.55)))
(apply 'command (append '("pline") coords '("c")))
(setq tap16 (ssadd (entlast) tap16))
(command "_mirror" (entlast) "" "5120,900" "5120,901" "No")
(setq tap16 (ssadd (entlast) tap16))
(setq coords (list 
(list 5120.4662 868.18) 
(list 5120.4559 868.18) 
(list 5120.4557 868.1903) 
(list 5120.4543 868.2006) 
(list 5120.4518 868.2108) 
(list 5120.4484 868.2211) 
(list 5120.444 868.2314) 
(list 5120.4388 868.2417) 
(list 5120.433 868.2519) 
(list 5120.4267 868.2622) 
(list 5120.4201 868.2725) 
(list 5120.4134 868.2828) 
(list 5120.4069 868.2931) 
(list 5120.4006 868.3033) 
(list 5120.3949 868.3136) 
(list 5120.3899 868.3239) 
(list 5120.3857 868.3342) 
(list 5120.3826 868.3444) 
(list 5120.3806 868.3547) 
(list 5120.3798 868.365) 
(list 5120.3802 868.3753) 
(list 5120.3818 868.3856) 
(list 5120.3846 868.3958) 
(list 5120.3886 868.4061) 
(list 5120.3936 868.4164) 
(list 5120.3995 868.4267) 
(list 5120.4061 868.4369) 
(list 5120.4133 868.4472) 
(list 5120.4207 868.4575) 
(list 5120.4282 868.4678) 
(list 5120.4356 868.4781) 
(list 5120.4426 868.4883) 
(list 5120.4491 868.4986) 
(list 5120.4547 868.5089) 
(list 5120.4594 868.5192) 
(list 5120.4629 868.5294) 
(list 5120.4652 868.5397) 
(list 5120.4662 868.55) 
(list 5120.4662 868.55)))
(apply 'command (append '("pline") coords '("c")))
(setq tap16 (ssadd (entlast) tap16))
(command "_mirror" (entlast) "" "5120,900" "5120,901" "No")
(setq tap16 (ssadd (entlast) tap16))
(setq coords (list 
(list 5121.137 868.18) 
(list 5120.4662 868.18) 
(list 5120.4662 868.1903) 
(list 5120.4662 868.2006) 
(list 5120.4662 868.2108) 
(list 5120.4662 868.2211) 
(list 5120.4662 868.2314) 
(list 5120.4662 868.2417) 
(list 5120.4662 868.2519) 
(list 5120.4662 868.2622) 
(list 5120.4662 868.2725) 
(list 5120.4662 868.2828) 
(list 5120.4662 868.2931) 
(list 5120.4662 868.3033) 
(list 5120.4662 868.3136) 
(list 5120.4662 868.3239) 
(list 5120.4662 868.3342) 
(list 5120.4662 868.3444) 
(list 5120.4662 868.3547) 
(list 5120.4662 868.365) 
(list 5120.4662 868.3753) 
(list 5120.4662 868.3856) 
(list 5120.4662 868.3958) 
(list 5120.4662 868.4061) 
(list 5120.4662 868.4164) 
(list 5120.4662 868.4267) 
(list 5120.4662 868.4369) 
(list 5120.4662 868.4472) 
(list 5120.4662 868.4575) 
(list 5120.4662 868.4678) 
(list 5120.4662 868.4781) 
(list 5120.4662 868.4883) 
(list 5120.4662 868.4986) 
(list 5120.4662 868.5089) 
(list 5120.4662 868.5192) 
(list 5120.4662 868.5294) 
(list 5120.4662 868.5397) 
(list 5120.4662 868.55) 
(list 5121.137 868.55)))
(apply 'command (append '("pline") coords '("c")))
(setq tap16 (ssadd (entlast) tap16))
(command "_mirror" (entlast) "" "5120,900" "5120,901" "No")
(setq tap16 (ssadd (entlast) tap16))
(setq coords (list 
(list 5120 868.55) 
(list 5120.135 868.55) 
(list 5120.135 868.5603) 
(list 5120.135 868.5706) 
(list 5120.135 868.5808) 
(list 5120.135 868.5911) 
(list 5120.135 868.6014) 
(list 5120.135 868.6117) 
(list 5120.135 868.6219) 
(list 5120.135 868.6322) 
(list 5120.135 868.6425) 
(list 5120.135 868.6528) 
(list 5120.135 868.6631) 
(list 5120.135 868.6733) 
(list 5120.135 868.6836) 
(list 5120.135 868.6939) 
(list 5120.135 868.7042) 
(list 5120.135 868.7144) 
(list 5120.135 868.7247) 
(list 5120.135 868.735) 
(list 5120.135 868.7453) 
(list 5120.135 868.7556) 
(list 5120.135 868.7658) 
(list 5120.135 868.7761) 
(list 5120.135 868.7864) 
(list 5120.135 868.7967) 
(list 5120.135 868.8069) 
(list 5120.135 868.8172) 
(list 5120.135 868.8275) 
(list 5120.135 868.8378) 
(list 5120.135 868.8481) 
(list 5120.135 868.8583) 
(list 5120.135 868.8686) 
(list 5120.135 868.8789) 
(list 5120.135 868.8892) 
(list 5120.135 868.8994) 
(list 5120.135 868.9097) 
(list 5120.135 868.92) 
(list 5120 868.92)))
(apply 'command (append '("pline") coords '("c")))
(setq tap16 (ssadd (entlast) tap16))
(command "_mirror" (entlast) "" "5120,900" "5120,901" "No")
(setq tap16 (ssadd (entlast) tap16))
(setq coords (list 
(list 5120.4764 868.55) 
(list 5120.4662 868.55) 
(list 5120.4658 868.5603) 
(list 5120.464 868.5706) 
(list 5120.4609 868.5808) 
(list 5120.4565 868.5911) 
(list 5120.451 868.6014) 
(list 5120.4445 868.6117) 
(list 5120.4373 868.6219) 
(list 5120.4295 868.6322) 
(list 5120.4213 868.6425) 
(list 5120.4131 868.6528) 
(list 5120.405 868.6631) 
(list 5120.3973 868.6733) 
(list 5120.3903 868.6836) 
(list 5120.3842 868.6939) 
(list 5120.3791 868.7042) 
(list 5120.3753 868.7144) 
(list 5120.3729 868.7247) 
(list 5120.3719 868.735) 
(list 5120.3725 868.7453) 
(list 5120.3745 868.7556) 
(list 5120.378 868.7658) 
(list 5120.3829 868.7761) 
(list 5120.389 868.7864) 
(list 5120.3962 868.7967) 
(list 5120.4042 868.8069) 
(list 5120.4129 868.8172) 
(list 5120.4219 868.8275) 
(list 5120.431 868.8378) 
(list 5120.4399 868.8481) 
(list 5120.4483 868.8583) 
(list 5120.4561 868.8686) 
(list 5120.4628 868.8789) 
(list 5120.4684 868.8892) 
(list 5120.4726 868.8994) 
(list 5120.4753 868.9097) 
(list 5120.4764 868.92) 
(list 5120.4764 868.92)))
(apply 'command (append '("pline") coords '("c")))
(setq tap16 (ssadd (entlast) tap16))
(command "_mirror" (entlast) "" "5120,900" "5120,901" "No")
(setq tap16 (ssadd (entlast) tap16))
(setq coords (list 
(list 5121.137 868.55) 
(list 5120.4764 868.55) 
(list 5120.4764 868.5603) 
(list 5120.4764 868.5706) 
(list 5120.4764 868.5808) 
(list 5120.4764 868.5911) 
(list 5120.4764 868.6014) 
(list 5120.4764 868.6117) 
(list 5120.4764 868.6219) 
(list 5120.4764 868.6322) 
(list 5120.4764 868.6425) 
(list 5120.4764 868.6528) 
(list 5120.4764 868.6631) 
(list 5120.4764 868.6733) 
(list 5120.4764 868.6836) 
(list 5120.4764 868.6939) 
(list 5120.4764 868.7042) 
(list 5120.4764 868.7144) 
(list 5120.4764 868.7247) 
(list 5120.4764 868.735) 
(list 5120.4764 868.7453) 
(list 5120.4764 868.7556) 
(list 5120.4764 868.7658) 
(list 5120.4764 868.7761) 
(list 5120.4764 868.7864) 
(list 5120.4764 868.7967) 
(list 5120.4764 868.8069) 
(list 5120.4764 868.8172) 
(list 5120.4764 868.8275) 
(list 5120.4764 868.8378) 
(list 5120.4764 868.8481) 
(list 5120.4764 868.8583) 
(list 5120.4764 868.8686) 
(list 5120.4764 868.8789) 
(list 5120.4764 868.8892) 
(list 5120.4764 868.8994) 
(list 5120.4764 868.9097) 
(list 5120.4764 868.92) 
(list 5121.137 868.92)))
(apply 'command (append '("pline") coords '("c")))
(setq tap16 (ssadd (entlast) tap16))
(command "_mirror" (entlast) "" "5120,900" "5120,901" "No")
(setq tap16 (ssadd (entlast) tap16))
(setq coords (list 
(list 5120 868.92) 
(list 5120.135 868.92) 
(list 5120.135 868.9303) 
(list 5120.135 868.9406) 
(list 5120.135 868.9508) 
(list 5120.135 868.9611) 
(list 5120.135 868.9714) 
(list 5120.135 868.9817) 
(list 5120.135 868.9919) 
(list 5120.135 869.0022) 
(list 5120.135 869.0125) 
(list 5120.135 869.0228) 
(list 5120.135 869.0331) 
(list 5120.135 869.0433) 
(list 5120.135 869.0536) 
(list 5120.135 869.0639) 
(list 5120.135 869.0742) 
(list 5120.135 869.0844) 
(list 5120.135 869.0947) 
(list 5120.135 869.105) 
(list 5120.135 869.1153) 
(list 5120.135 869.1256) 
(list 5120.135 869.1358) 
(list 5120.135 869.1461) 
(list 5120.135 869.1564) 
(list 5120.135 869.1667) 
(list 5120.135 869.1769) 
(list 5120.135 869.1872) 
(list 5120.135 869.1975) 
(list 5120.135 869.2078) 
(list 5120.135 869.2181) 
(list 5120.135 869.2283) 
(list 5120.135 869.2386) 
(list 5120.135 869.2489) 
(list 5120.135 869.2592) 
(list 5120.135 869.2694) 
(list 5120.135 869.2797) 
(list 5120.135 869.29) 
(list 5120 869.29)))
(apply 'command (append '("pline") coords '("c")))
(setq tap16 (ssadd (entlast) tap16))
(command "_mirror" (entlast) "" "5120,900" "5120,901" "No")
(setq tap16 (ssadd (entlast) tap16))
(setq coords (list 
(list 5120.4866 868.92) 
(list 5120.4764 868.92) 
(list 5120.4759 868.9303) 
(list 5120.4737 868.9406) 
(list 5120.4699 868.9508) 
(list 5120.4646 868.9611) 
(list 5120.458 868.9714) 
(list 5120.4503 868.9817) 
(list 5120.4416 868.9919) 
(list 5120.4322 869.0022) 
(list 5120.4225 869.0125) 
(list 5120.4127 869.0228) 
(list 5120.4031 869.0331) 
(list 5120.394 869.0433) 
(list 5120.3857 869.0536) 
(list 5120.3785 869.0639) 
(list 5120.3725 869.0742) 
(list 5120.368 869.0844) 
(list 5120.3652 869.0947) 
(list 5120.3641 869.105) 
(list 5120.3648 869.1153) 
(list 5120.3672 869.1256) 
(list 5120.3714 869.1358) 
(list 5120.3772 869.1461) 
(list 5120.3844 869.1564) 
(list 5120.3929 869.1667) 
(list 5120.4024 869.1769) 
(list 5120.4125 869.1872) 
(list 5120.4231 869.1975) 
(list 5120.4338 869.2078) 
(list 5120.4442 869.2181) 
(list 5120.4541 869.2283) 
(list 5120.4631 869.2386) 
(list 5120.4709 869.2489) 
(list 5120.4774 869.2592) 
(list 5120.4823 869.2694) 
(list 5120.4854 869.2797) 
(list 5120.4866 869.29) 
(list 5120.4866 869.29)))
(apply 'command (append '("pline") coords '("c")))
(setq tap16 (ssadd (entlast) tap16))
(command "_mirror" (entlast) "" "5120,900" "5120,901" "No")
(setq tap16 (ssadd (entlast) tap16))
(setq coords (list 
(list 5121.137 868.92) 
(list 5120.4866 868.92) 
(list 5120.4866 868.9303) 
(list 5120.4866 868.9406) 
(list 5120.4866 868.9508) 
(list 5120.4866 868.9611) 
(list 5120.4866 868.9714) 
(list 5120.4866 868.9817) 
(list 5120.4866 868.9919) 
(list 5120.4866 869.0022) 
(list 5120.4866 869.0125) 
(list 5120.4866 869.0228) 
(list 5120.4866 869.0331) 
(list 5120.4866 869.0433) 
(list 5120.4866 869.0536) 
(list 5120.4866 869.0639) 
(list 5120.4866 869.0742) 
(list 5120.4866 869.0844) 
(list 5120.4866 869.0947) 
(list 5120.4866 869.105) 
(list 5120.4866 869.1153) 
(list 5120.4866 869.1256) 
(list 5120.4866 869.1358) 
(list 5120.4866 869.1461) 
(list 5120.4866 869.1564) 
(list 5120.4866 869.1667) 
(list 5120.4866 869.1769) 
(list 5120.4866 869.1872) 
(list 5120.4866 869.1975) 
(list 5120.4866 869.2078) 
(list 5120.4866 869.2181) 
(list 5120.4866 869.2283) 
(list 5120.4866 869.2386) 
(list 5120.4866 869.2489) 
(list 5120.4866 869.2592) 
(list 5120.4866 869.2694) 
(list 5120.4866 869.2797) 
(list 5120.4866 869.29) 
(list 5121.137 869.29)))
(apply 'command (append '("pline") coords '("c")))
(setq tap16 (ssadd (entlast) tap16))
(command "_mirror" (entlast) "" "5120,900" "5120,901" "No")
(setq tap16 (ssadd (entlast) tap16))
(setq coords (list 
(list 5120 869.29) 
(list 5120.135 869.29) 
(list 5120.135 869.3003) 
(list 5120.135 869.3106) 
(list 5120.135 869.3208) 
(list 5120.135 869.3311) 
(list 5120.135 869.3414) 
(list 5120.135 869.3517) 
(list 5120.135 869.3619) 
(list 5120.135 869.3722) 
(list 5120.135 869.3825) 
(list 5120.135 869.3928) 
(list 5120.135 869.4031) 
(list 5120.135 869.4133) 
(list 5120.135 869.4236) 
(list 5120.135 869.4339) 
(list 5120.135 869.4442) 
(list 5120.135 869.4544) 
(list 5120.135 869.4647) 
(list 5120.135 869.475) 
(list 5120.135 869.4853) 
(list 5120.135 869.4956) 
(list 5120.135 869.5058) 
(list 5120.135 869.5161) 
(list 5120.135 869.5264) 
(list 5120.135 869.5367) 
(list 5120.135 869.5469) 
(list 5120.135 869.5572) 
(list 5120.135 869.5675) 
(list 5120.135 869.5778) 
(list 5120.135 869.5881) 
(list 5120.135 869.5983) 
(list 5120.135 869.6086) 
(list 5120.135 869.6189) 
(list 5120.135 869.6292) 
(list 5120.135 869.6394) 
(list 5120.135 869.6497) 
(list 5120.135 869.66) 
(list 5120 869.66)))
(apply 'command (append '("pline") coords '("c")))
(setq tap16 (ssadd (entlast) tap16))
(command "_mirror" (entlast) "" "5120,900" "5120,901" "No")
(setq tap16 (ssadd (entlast) tap16))
(setq coords (list 
(list 5120.4969 869.29) 
(list 5120.4866 869.29) 
(list 5120.486 869.3003) 
(list 5120.4834 869.3106) 
(list 5120.4789 869.3208) 
(list 5120.4727 869.3311) 
(list 5120.465 869.3414) 
(list 5120.456 869.3517) 
(list 5120.4459 869.3619) 
(list 5120.435 869.3722) 
(list 5120.4237 869.3825) 
(list 5120.4123 869.3928) 
(list 5120.4012 869.4031) 
(list 5120.3907 869.4133) 
(list 5120.3811 869.4236) 
(list 5120.3727 869.4339) 
(list 5120.3659 869.4442) 
(list 5120.3607 869.4544) 
(list 5120.3575 869.4647) 
(list 5120.3562 869.475) 
(list 5120.3571 869.4853) 
(list 5120.3599 869.4956) 
(list 5120.3648 869.5058) 
(list 5120.3715 869.5161) 
(list 5120.3798 869.5264) 
(list 5120.3896 869.5367) 
(list 5120.4005 869.5469) 
(list 5120.4122 869.5572) 
(list 5120.4243 869.5675) 
(list 5120.4365 869.5778) 
(list 5120.4485 869.5881) 
(list 5120.4598 869.5983) 
(list 5120.4701 869.6086) 
(list 5120.4791 869.6189) 
(list 5120.4864 869.6292) 
(list 5120.492 869.6394) 
(list 5120.4955 869.6497) 
(list 5120.4969 869.66) 
(list 5120.4969 869.66)))
(apply 'command (append '("pline") coords '("c")))
(setq tap16 (ssadd (entlast) tap16))
(command "_mirror" (entlast) "" "5120,900" "5120,901" "No")
(setq tap16 (ssadd (entlast) tap16))
(setq coords (list 
(list 5121.137 869.29) 
(list 5120.4969 869.29) 
(list 5120.4969 869.3003) 
(list 5120.4969 869.3106) 
(list 5120.4969 869.3208) 
(list 5120.4969 869.3311) 
(list 5120.4969 869.3414) 
(list 5120.4969 869.3517) 
(list 5120.4969 869.3619) 
(list 5120.4969 869.3722) 
(list 5120.4969 869.3825) 
(list 5120.4969 869.3928) 
(list 5120.4969 869.4031) 
(list 5120.4969 869.4133) 
(list 5120.4969 869.4236) 
(list 5120.4969 869.4339) 
(list 5120.4969 869.4442) 
(list 5120.4969 869.4544) 
(list 5120.4969 869.4647) 
(list 5120.4969 869.475) 
(list 5120.4969 869.4853) 
(list 5120.4969 869.4956) 
(list 5120.4969 869.5058) 
(list 5120.4969 869.5161) 
(list 5120.4969 869.5264) 
(list 5120.4969 869.5367) 
(list 5120.4969 869.5469) 
(list 5120.4969 869.5572) 
(list 5120.4969 869.5675) 
(list 5120.4969 869.5778) 
(list 5120.4969 869.5881) 
(list 5120.4969 869.5983) 
(list 5120.4969 869.6086) 
(list 5120.4969 869.6189) 
(list 5120.4969 869.6292) 
(list 5120.4969 869.6394) 
(list 5120.4969 869.6497) 
(list 5120.4969 869.66) 
(list 5121.137 869.66)))
(apply 'command (append '("pline") coords '("c")))
(setq tap16 (ssadd (entlast) tap16))
(command "_mirror" (entlast) "" "5120,900" "5120,901" "No")
(setq tap16 (ssadd (entlast) tap16))
(setq coords (list 
(list 5120 869.66) 
(list 5120.135 869.66) 
(list 5120.135 869.6703) 
(list 5120.135 869.6806) 
(list 5120.135 869.6908) 
(list 5120.135 869.7011) 
(list 5120.135 869.7114) 
(list 5120.135 869.7217) 
(list 5120.135 869.7319) 
(list 5120.135 869.7422) 
(list 5120.135 869.7525) 
(list 5120.135 869.7628) 
(list 5120.135 869.7731) 
(list 5120.135 869.7833) 
(list 5120.135 869.7936) 
(list 5120.135 869.8039) 
(list 5120.135 869.8142) 
(list 5120.135 869.8244) 
(list 5120.135 869.8347) 
(list 5120.135 869.845) 
(list 5120.135 869.8553) 
(list 5120.135 869.8656) 
(list 5120.135 869.8758) 
(list 5120.135 869.8861) 
(list 5120.135 869.8964) 
(list 5120.135 869.9067) 
(list 5120.135 869.9169) 
(list 5120.135 869.9272) 
(list 5120.135 869.9375) 
(list 5120.135 869.9478) 
(list 5120.135 869.9581) 
(list 5120.135 869.9683) 
(list 5120.135 869.9786) 
(list 5120.135 869.9889) 
(list 5120.135 869.9992) 
(list 5120.135 870.0094) 
(list 5120.135 870.0197) 
(list 5120.135 870.03) 
(list 5120 870.03)))
(apply 'command (append '("pline") coords '("c")))
(setq tap16 (ssadd (entlast) tap16))
(command "_mirror" (entlast) "" "5120,900" "5120,901" "No")
(setq tap16 (ssadd (entlast) tap16))
(setq coords (list 
(list 5120.5071 869.66) 
(list 5120.4969 869.66) 
(list 5120.496 869.6703) 
(list 5120.493 869.6806) 
(list 5120.4879 869.6908) 
(list 5120.4809 869.7011) 
(list 5120.472 869.7114) 
(list 5120.4617 869.7217) 
(list 5120.4502 869.7319) 
(list 5120.4378 869.7422) 
(list 5120.4249 869.7525) 
(list 5120.4119 869.7628) 
(list 5120.3993 869.7731) 
(list 5120.3874 869.7833) 
(list 5120.3765 869.7936) 
(list 5120.367 869.8039) 
(list 5120.3593 869.8142) 
(list 5120.3535 869.8244) 
(list 5120.3498 869.8347) 
(list 5120.3484 869.845) 
(list 5120.3494 869.8553) 
(list 5120.3526 869.8656) 
(list 5120.3582 869.8758) 
(list 5120.3657 869.8861) 
(list 5120.3752 869.8964) 
(list 5120.3863 869.9067) 
(list 5120.3986 869.9169) 
(list 5120.4118 869.9272) 
(list 5120.4255 869.9375) 
(list 5120.4393 869.9478) 
(list 5120.4528 869.9581) 
(list 5120.4655 869.9683) 
(list 5120.4771 869.9786) 
(list 5120.4872 869.9889) 
(list 5120.4955 869.9992) 
(list 5120.5017 870.0094) 
(list 5120.5056 870.0197) 
(list 5120.5071 870.03) 
(list 5120.5071 870.03)))
(apply 'command (append '("pline") coords '("c")))
(setq tap16 (ssadd (entlast) tap16))
(command "_mirror" (entlast) "" "5120,900" "5120,901" "No")
(setq tap16 (ssadd (entlast) tap16))
(setq coords (list 
(list 5121.137 869.66) 
(list 5120.5071 869.66) 
(list 5120.5071 869.6703) 
(list 5120.5071 869.6806) 
(list 5120.5071 869.6908) 
(list 5120.5071 869.7011) 
(list 5120.5071 869.7114) 
(list 5120.5071 869.7217) 
(list 5120.5071 869.7319) 
(list 5120.5071 869.7422) 
(list 5120.5071 869.7525) 
(list 5120.5071 869.7628) 
(list 5120.5071 869.7731) 
(list 5120.5071 869.7833) 
(list 5120.5071 869.7936) 
(list 5120.5071 869.8039) 
(list 5120.5071 869.8142) 
(list 5120.5071 869.8244) 
(list 5120.5071 869.8347) 
(list 5120.5071 869.845) 
(list 5120.5071 869.8553) 
(list 5120.5071 869.8656) 
(list 5120.5071 869.8758) 
(list 5120.5071 869.8861) 
(list 5120.5071 869.8964) 
(list 5120.5071 869.9067) 
(list 5120.5071 869.9169) 
(list 5120.5071 869.9272) 
(list 5120.5071 869.9375) 
(list 5120.5071 869.9478) 
(list 5120.5071 869.9581) 
(list 5120.5071 869.9683) 
(list 5120.5071 869.9786) 
(list 5120.5071 869.9889) 
(list 5120.5071 869.9992) 
(list 5120.5071 870.0094) 
(list 5120.5071 870.0197) 
(list 5120.5071 870.03) 
(list 5121.137 870.03)))
(apply 'command (append '("pline") coords '("c")))
(setq tap16 (ssadd (entlast) tap16))
(command "_mirror" (entlast) "" "5120,900" "5120,901" "No")
(setq tap16 (ssadd (entlast) tap16))
(setq coords (list 
(list 5120 870.03) 
(list 5120.135 870.03) 
(list 5120.135 870.0403) 
(list 5120.135 870.0506) 
(list 5120.135 870.0608) 
(list 5120.135 870.0711) 
(list 5120.135 870.0814) 
(list 5120.135 870.0917) 
(list 5120.135 870.1019) 
(list 5120.135 870.1122) 
(list 5120.135 870.1225) 
(list 5120.135 870.1328) 
(list 5120.135 870.1431) 
(list 5120.135 870.1533) 
(list 5120.135 870.1636) 
(list 5120.135 870.1739) 
(list 5120.135 870.1842) 
(list 5120.135 870.1944) 
(list 5120.135 870.2047) 
(list 5120.135 870.215) 
(list 5120.135 870.2253) 
(list 5120.135 870.2356) 
(list 5120.135 870.2458) 
(list 5120.135 870.2561) 
(list 5120.135 870.2664) 
(list 5120.135 870.2767) 
(list 5120.135 870.2869) 
(list 5120.135 870.2972) 
(list 5120.135 870.3075) 
(list 5120.135 870.3178) 
(list 5120.135 870.3281) 
(list 5120.135 870.3383) 
(list 5120.135 870.3486) 
(list 5120.135 870.3589) 
(list 5120.135 870.3692) 
(list 5120.135 870.3794) 
(list 5120.135 870.3897) 
(list 5120.135 870.4) 
(list 5120 870.4)))
(apply 'command (append '("pline") coords '("c")))
(setq tap16 (ssadd (entlast) tap16))
(command "_mirror" (entlast) "" "5120,900" "5120,901" "No")
(setq tap16 (ssadd (entlast) tap16))
(setq coords (list 
(list 5120.5173 870.03) 
(list 5120.5071 870.03) 
(list 5120.5061 870.0403) 
(list 5120.5027 870.0506) 
(list 5120.497 870.0608) 
(list 5120.489 870.0711) 
(list 5120.479 870.0814) 
(list 5120.4674 870.0917) 
(list 5120.4544 870.1019) 
(list 5120.4405 870.1122) 
(list 5120.4261 870.1225) 
(list 5120.4116 870.1328) 
(list 5120.3974 870.1431) 
(list 5120.384 870.1533) 
(list 5120.3719 870.1636) 
(list 5120.3613 870.1739) 
(list 5120.3526 870.1842) 
(list 5120.3462 870.1944) 
(list 5120.3421 870.2047) 
(list 5120.3406 870.215) 
(list 5120.3417 870.2253) 
(list 5120.3454 870.2356) 
(list 5120.3515 870.2458) 
(list 5120.36 870.2561) 
(list 5120.3706 870.2664) 
(list 5120.3829 870.2767) 
(list 5120.3967 870.2869) 
(list 5120.4114 870.2972) 
(list 5120.4267 870.3075) 
(list 5120.4421 870.3178) 
(list 5120.4571 870.3281) 
(list 5120.4712 870.3383) 
(list 5120.4841 870.3486) 
(list 5120.4953 870.3589) 
(list 5120.5045 870.3692) 
(list 5120.5113 870.3794) 
(list 5120.5157 870.3897) 
(list 5120.5173 870.4) 
(list 5120.5173 870.4)))
(apply 'command (append '("pline") coords '("c")))
(setq tap16 (ssadd (entlast) tap16))
(command "_mirror" (entlast) "" "5120,900" "5120,901" "No")
(setq tap16 (ssadd (entlast) tap16))
(setq coords (list 
(list 5121.137 870.03) 
(list 5120.5173 870.03) 
(list 5120.5173 870.0403) 
(list 5120.5173 870.0506) 
(list 5120.5173 870.0608) 
(list 5120.5173 870.0711) 
(list 5120.5173 870.0814) 
(list 5120.5173 870.0917) 
(list 5120.5173 870.1019) 
(list 5120.5173 870.1122) 
(list 5120.5173 870.1225) 
(list 5120.5173 870.1328) 
(list 5120.5173 870.1431) 
(list 5120.5173 870.1533) 
(list 5120.5173 870.1636) 
(list 5120.5173 870.1739) 
(list 5120.5173 870.1842) 
(list 5120.5173 870.1944) 
(list 5120.5173 870.2047) 
(list 5120.5173 870.215) 
(list 5120.5173 870.2253) 
(list 5120.5173 870.2356) 
(list 5120.5173 870.2458) 
(list 5120.5173 870.2561) 
(list 5120.5173 870.2664) 
(list 5120.5173 870.2767) 
(list 5120.5173 870.2869) 
(list 5120.5173 870.2972) 
(list 5120.5173 870.3075) 
(list 5120.5173 870.3178) 
(list 5120.5173 870.3281) 
(list 5120.5173 870.3383) 
(list 5120.5173 870.3486) 
(list 5120.5173 870.3589) 
(list 5120.5173 870.3692) 
(list 5120.5173 870.3794) 
(list 5120.5173 870.3897) 
(list 5120.5173 870.4) 
(list 5121.137 870.4)))
(apply 'command (append '("pline") coords '("c")))
(setq tap16 (ssadd (entlast) tap16))
(command "_mirror" (entlast) "" "5120,900" "5120,901" "No")
(setq tap16 (ssadd (entlast) tap16))
(setq coords (list 
(list 5120 870.4) 
(list 5120.135 870.4) 
(list 5120.135 870.4103) 
(list 5120.135 870.4206) 
(list 5120.135 870.4308) 
(list 5120.135 870.4411) 
(list 5120.135 870.4514) 
(list 5120.135 870.4617) 
(list 5120.135 870.4719) 
(list 5120.135 870.4822) 
(list 5120.135 870.4925) 
(list 5120.135 870.5028) 
(list 5120.135 870.5131) 
(list 5120.135 870.5233) 
(list 5120.135 870.5336) 
(list 5120.135 870.5439) 
(list 5120.135 870.5542) 
(list 5120.135 870.5644) 
(list 5120.135 870.5747) 
(list 5120.135 870.585) 
(list 5120.135 870.5953) 
(list 5120.135 870.6056) 
(list 5120.135 870.6158) 
(list 5120.135 870.6261) 
(list 5120.135 870.6364) 
(list 5120.135 870.6467) 
(list 5120.135 870.6569) 
(list 5120.135 870.6672) 
(list 5120.135 870.6775) 
(list 5120.135 870.6878) 
(list 5120.135 870.6981) 
(list 5120.135 870.7083) 
(list 5120.135 870.7186) 
(list 5120.135 870.7289) 
(list 5120.135 870.7392) 
(list 5120.135 870.7494) 
(list 5120.135 870.7597) 
(list 5120.135 870.77) 
(list 5120 870.77)))
(apply 'command (append '("pline") coords '("c")))
(setq tap16 (ssadd (entlast) tap16))
(command "_mirror" (entlast) "" "5120,900" "5120,901" "No")
(setq tap16 (ssadd (entlast) tap16))
(setq coords (list 
(list 5120.5276 870.4) 
(list 5120.5173 870.4) 
(list 5120.5162 870.4103) 
(list 5120.5124 870.4206) 
(list 5120.506 870.4308) 
(list 5120.4971 870.4411) 
(list 5120.486 870.4514) 
(list 5120.4731 870.4617) 
(list 5120.4587 870.4719) 
(list 5120.4433 870.4822) 
(list 5120.4273 870.4925) 
(list 5120.4112 870.5028) 
(list 5120.3955 870.5131) 
(list 5120.3807 870.5233) 
(list 5120.3673 870.5336) 
(list 5120.3556 870.5439) 
(list 5120.346 870.5542) 
(list 5120.3389 870.5644) 
(list 5120.3344 870.5747) 
(list 5120.3327 870.585) 
(list 5120.334 870.5953) 
(list 5120.3381 870.6056) 
(list 5120.3449 870.6158) 
(list 5120.3543 870.6261) 
(list 5120.366 870.6364) 
(list 5120.3796 870.6467) 
(list 5120.3948 870.6569) 
(list 5120.411 870.6672) 
(list 5120.4279 870.6775) 
(list 5120.4448 870.6878) 
(list 5120.4614 870.6981) 
(list 5120.4769 870.7083) 
(list 5120.4911 870.7186) 
(list 5120.5034 870.7289) 
(list 5120.5135 870.7392) 
(list 5120.521 870.7494) 
(list 5120.5258 870.7597) 
(list 5120.5276 870.77) 
(list 5120.5276 870.77)))
(apply 'command (append '("pline") coords '("c")))
(setq tap16 (ssadd (entlast) tap16))
(command "_mirror" (entlast) "" "5120,900" "5120,901" "No")
(setq tap16 (ssadd (entlast) tap16))
(setq coords (list 
(list 5121.137 870.4) 
(list 5120.5276 870.4) 
(list 5120.5276 870.4103) 
(list 5120.5276 870.4206) 
(list 5120.5276 870.4308) 
(list 5120.5276 870.4411) 
(list 5120.5276 870.4514) 
(list 5120.5276 870.4617) 
(list 5120.5276 870.4719) 
(list 5120.5276 870.4822) 
(list 5120.5276 870.4925) 
(list 5120.5276 870.5028) 
(list 5120.5276 870.5131) 
(list 5120.5276 870.5233) 
(list 5120.5276 870.5336) 
(list 5120.5276 870.5439) 
(list 5120.5276 870.5542) 
(list 5120.5276 870.5644) 
(list 5120.5276 870.5747) 
(list 5120.5276 870.585) 
(list 5120.5276 870.5953) 
(list 5120.5276 870.6056) 
(list 5120.5276 870.6158) 
(list 5120.5276 870.6261) 
(list 5120.5276 870.6364) 
(list 5120.5276 870.6467) 
(list 5120.5276 870.6569) 
(list 5120.5276 870.6672) 
(list 5120.5276 870.6775) 
(list 5120.5276 870.6878) 
(list 5120.5276 870.6981) 
(list 5120.5276 870.7083) 
(list 5120.5276 870.7186) 
(list 5120.5276 870.7289) 
(list 5120.5276 870.7392) 
(list 5120.5276 870.7494) 
(list 5120.5276 870.7597) 
(list 5120.5276 870.77) 
(list 5121.137 870.77)))
(apply 'command (append '("pline") coords '("c")))
(setq tap16 (ssadd (entlast) tap16))
(command "_mirror" (entlast) "" "5120,900" "5120,901" "No")
(setq tap16 (ssadd (entlast) tap16))
(setq coords (list 
(list 5120 870.77) 
(list 5120.135 870.77) 
(list 5120.135 870.7803) 
(list 5120.135 870.7906) 
(list 5120.135 870.8008) 
(list 5120.135 870.8111) 
(list 5120.135 870.8214) 
(list 5120.135 870.8317) 
(list 5120.135 870.8419) 
(list 5120.135 870.8522) 
(list 5120.135 870.8625) 
(list 5120.135 870.8728) 
(list 5120.135 870.8831) 
(list 5120.135 870.8933) 
(list 5120.135 870.9036) 
(list 5120.135 870.9139) 
(list 5120.135 870.9242) 
(list 5120.135 870.9344) 
(list 5120.135 870.9447) 
(list 5120.135 870.955) 
(list 5120.135 870.9653) 
(list 5120.135 870.9756) 
(list 5120.135 870.9858) 
(list 5120.135 870.9961) 
(list 5120.135 871.0064) 
(list 5120.135 871.0167) 
(list 5120.135 871.0269) 
(list 5120.135 871.0372) 
(list 5120.135 871.0475) 
(list 5120.135 871.0578) 
(list 5120.135 871.0681) 
(list 5120.135 871.0783) 
(list 5120.135 871.0886) 
(list 5120.135 871.0989) 
(list 5120.135 871.1092) 
(list 5120.135 871.1194) 
(list 5120.135 871.1297) 
(list 5120.135 871.14) 
(list 5120 871.14)))
(apply 'command (append '("pline") coords '("c")))
(setq tap16 (ssadd (entlast) tap16))
(command "_mirror" (entlast) "" "5120,900" "5120,901" "No")
(setq tap16 (ssadd (entlast) tap16))
(setq coords (list 
(list 5120.5378 870.77) 
(list 5120.5276 870.77) 
(list 5120.5263 870.7803) 
(list 5120.5221 870.7906) 
(list 5120.515 870.8008) 
(list 5120.5052 870.8111) 
(list 5120.493 870.8214) 
(list 5120.4788 870.8317) 
(list 5120.463 870.8419) 
(list 5120.4461 870.8522) 
(list 5120.4285 870.8625) 
(list 5120.4108 870.8728) 
(list 5120.3936 870.8831) 
(list 5120.3774 870.8933) 
(list 5120.3627 870.9036) 
(list 5120.3499 870.9139) 
(list 5120.3394 870.9242) 
(list 5120.3316 870.9344) 
(list 5120.3267 870.9447) 
(list 5120.3249 870.955) 
(list 5120.3263 870.9653) 
(list 5120.3308 870.9756) 
(list 5120.3383 870.9858) 
(list 5120.3486 870.9961) 
(list 5120.3614 871.0064) 
(list 5120.3763 871.0167) 
(list 5120.3929 871.0269) 
(list 5120.4107 871.0372) 
(list 5120.4291 871.0475) 
(list 5120.4476 871.0578) 
(list 5120.4656 871.0681) 
(list 5120.4826 871.0783) 
(list 5120.4981 871.0886) 
(list 5120.5115 871.0989) 
(list 5120.5225 871.1092) 
(list 5120.5307 871.1194) 
(list 5120.5359 871.1297) 
(list 5120.5378 871.14) 
(list 5120.5378 871.14)))
(apply 'command (append '("pline") coords '("c")))
(setq tap16 (ssadd (entlast) tap16))
(command "_mirror" (entlast) "" "5120,900" "5120,901" "No")
(setq tap16 (ssadd (entlast) tap16))
(setq coords (list 
(list 5121.137 870.77) 
(list 5120.5378 870.77) 
(list 5120.5378 870.7803) 
(list 5120.5378 870.7906) 
(list 5120.5378 870.8008) 
(list 5120.5378 870.8111) 
(list 5120.5378 870.8214) 
(list 5120.5378 870.8317) 
(list 5120.5378 870.8419) 
(list 5120.5378 870.8522) 
(list 5120.5378 870.8625) 
(list 5120.5378 870.8728) 
(list 5120.5378 870.8831) 
(list 5120.5378 870.8933) 
(list 5120.5378 870.9036) 
(list 5120.5378 870.9139) 
(list 5120.5378 870.9242) 
(list 5120.5378 870.9344) 
(list 5120.5378 870.9447) 
(list 5120.5378 870.955) 
(list 5120.5378 870.9653) 
(list 5120.5378 870.9756) 
(list 5120.5378 870.9858) 
(list 5120.5378 870.9961) 
(list 5120.5378 871.0064) 
(list 5120.5378 871.0167) 
(list 5120.5378 871.0269) 
(list 5120.5378 871.0372) 
(list 5120.5378 871.0475) 
(list 5120.5378 871.0578) 
(list 5120.5378 871.0681) 
(list 5120.5378 871.0783) 
(list 5120.5378 871.0886) 
(list 5120.5378 871.0989) 
(list 5120.5378 871.1092) 
(list 5120.5378 871.1194) 
(list 5120.5378 871.1297) 
(list 5120.5378 871.14) 
(list 5121.137 871.14)))
(apply 'command (append '("pline") coords '("c")))
(setq tap16 (ssadd (entlast) tap16))
(command "_mirror" (entlast) "" "5120,900" "5120,901" "No")
(setq tap16 (ssadd (entlast) tap16))
(setq coords (list 
(list 5120 871.14) 
(list 5120.135 871.14) 
(list 5120.135 871.1503) 
(list 5120.135 871.1606) 
(list 5120.135 871.1708) 
(list 5120.135 871.1811) 
(list 5120.135 871.1914) 
(list 5120.135 871.2017) 
(list 5120.135 871.2119) 
(list 5120.135 871.2222) 
(list 5120.135 871.2325) 
(list 5120.135 871.2428) 
(list 5120.135 871.2531) 
(list 5120.135 871.2633) 
(list 5120.135 871.2736) 
(list 5120.135 871.2839) 
(list 5120.135 871.2942) 
(list 5120.135 871.3044) 
(list 5120.135 871.3147) 
(list 5120.135 871.325) 
(list 5120.135 871.3353) 
(list 5120.135 871.3456) 
(list 5120.135 871.3558) 
(list 5120.135 871.3661) 
(list 5120.135 871.3764) 
(list 5120.135 871.3867) 
(list 5120.135 871.3969) 
(list 5120.135 871.4072) 
(list 5120.135 871.4175) 
(list 5120.135 871.4278) 
(list 5120.135 871.4381) 
(list 5120.135 871.4483) 
(list 5120.135 871.4586) 
(list 5120.135 871.4689) 
(list 5120.135 871.4792) 
(list 5120.135 871.4894) 
(list 5120.135 871.4997) 
(list 5120.135 871.51) 
(list 5120 871.51)))
(apply 'command (append '("pline") coords '("c")))
(setq tap16 (ssadd (entlast) tap16))
(command "_mirror" (entlast) "" "5120,900" "5120,901" "No")
(setq tap16 (ssadd (entlast) tap16))
(setq coords (list 
(list 5120.548 871.14) 
(list 5120.5378 871.14) 
(list 5120.5364 871.1503) 
(list 5120.5318 871.1606) 
(list 5120.524 871.1708) 
(list 5120.5133 871.1811) 
(list 5120.5001 871.1914) 
(list 5120.4846 871.2017) 
(list 5120.4673 871.2119) 
(list 5120.4488 871.2222) 
(list 5120.4297 871.2325) 
(list 5120.4105 871.2428) 
(list 5120.3917 871.2531) 
(list 5120.3741 871.2633) 
(list 5120.3581 871.2736) 
(list 5120.3441 871.2839) 
(list 5120.3328 871.2942) 
(list 5120.3243 871.3044) 
(list 5120.319 871.3147) 
(list 5120.3171 871.325) 
(list 5120.3186 871.3353) 
(list 5120.3235 871.3456) 
(list 5120.3317 871.3558) 
(list 5120.3429 871.3661) 
(list 5120.3568 871.3764) 
(list 5120.373 871.3867) 
(list 5120.391 871.3969) 
(list 5120.4103 871.4072) 
(list 5120.4303 871.4175) 
(list 5120.4504 871.4278) 
(list 5120.4699 871.4381) 
(list 5120.4884 871.4483) 
(list 5120.5051 871.4586) 
(list 5120.5197 871.4689) 
(list 5120.5315 871.4792) 
(list 5120.5404 871.4894) 
(list 5120.546 871.4997) 
(list 5120.548 871.51) 
(list 5120.548 871.51)))
(apply 'command (append '("pline") coords '("c")))
(setq tap16 (ssadd (entlast) tap16))
(command "_mirror" (entlast) "" "5120,900" "5120,901" "No")
(setq tap16 (ssadd (entlast) tap16))
(setq coords (list 
(list 5121.137 871.14) 
(list 5120.548 871.14) 
(list 5120.548 871.1503) 
(list 5120.548 871.1606) 
(list 5120.548 871.1708) 
(list 5120.548 871.1811) 
(list 5120.548 871.1914) 
(list 5120.548 871.2017) 
(list 5120.548 871.2119) 
(list 5120.548 871.2222) 
(list 5120.548 871.2325) 
(list 5120.548 871.2428) 
(list 5120.548 871.2531) 
(list 5120.548 871.2633) 
(list 5120.548 871.2736) 
(list 5120.548 871.2839) 
(list 5120.548 871.2942) 
(list 5120.548 871.3044) 
(list 5120.548 871.3147) 
(list 5120.548 871.325) 
(list 5120.548 871.3353) 
(list 5120.548 871.3456) 
(list 5120.548 871.3558) 
(list 5120.548 871.3661) 
(list 5120.548 871.3764) 
(list 5120.548 871.3867) 
(list 5120.548 871.3969) 
(list 5120.548 871.4072) 
(list 5120.548 871.4175) 
(list 5120.548 871.4278) 
(list 5120.548 871.4381) 
(list 5120.548 871.4483) 
(list 5120.548 871.4586) 
(list 5120.548 871.4689) 
(list 5120.548 871.4792) 
(list 5120.548 871.4894) 
(list 5120.548 871.4997) 
(list 5120.548 871.51) 
(list 5121.137 871.51)))
(apply 'command (append '("pline") coords '("c")))
(setq tap16 (ssadd (entlast) tap16))
(command "_mirror" (entlast) "" "5120,900" "5120,901" "No")
(setq tap16 (ssadd (entlast) tap16))
(setq coords (list 
(list 5120 871.51) 
(list 5120.135 871.51) 
(list 5120.135 871.5203) 
(list 5120.135 871.5306) 
(list 5120.135 871.5408) 
(list 5120.135 871.5511) 
(list 5120.135 871.5614) 
(list 5120.135 871.5717) 
(list 5120.135 871.5819) 
(list 5120.135 871.5922) 
(list 5120.135 871.6025) 
(list 5120.135 871.6128) 
(list 5120.135 871.6231) 
(list 5120.135 871.6333) 
(list 5120.135 871.6436) 
(list 5120.135 871.6539) 
(list 5120.135 871.6642) 
(list 5120.135 871.6744) 
(list 5120.135 871.6847) 
(list 5120.135 871.695) 
(list 5120.135 871.7053) 
(list 5120.135 871.7156) 
(list 5120.135 871.7258) 
(list 5120.135 871.7361) 
(list 5120.135 871.7464) 
(list 5120.135 871.7567) 
(list 5120.135 871.7669) 
(list 5120.135 871.7772) 
(list 5120.135 871.7875) 
(list 5120.135 871.7978) 
(list 5120.135 871.8081) 
(list 5120.135 871.8183) 
(list 5120.135 871.8286) 
(list 5120.135 871.8389) 
(list 5120.135 871.8492) 
(list 5120.135 871.8594) 
(list 5120.135 871.8697) 
(list 5120.135 871.88) 
(list 5120 871.88)))
(apply 'command (append '("pline") coords '("c")))
(setq tap16 (ssadd (entlast) tap16))
(command "_mirror" (entlast) "" "5120,900" "5120,901" "No")
(setq tap16 (ssadd (entlast) tap16))
(setq coords (list 
(list 5120.5583 871.51) 
(list 5120.548 871.51) 
(list 5120.5465 871.5203) 
(list 5120.5415 871.5306) 
(list 5120.5331 871.5408) 
(list 5120.5215 871.5511) 
(list 5120.5071 871.5614) 
(list 5120.4903 871.5717) 
(list 5120.4716 871.5819) 
(list 5120.4516 871.5922) 
(list 5120.4309 871.6025) 
(list 5120.4101 871.6128) 
(list 5120.3899 871.6231) 
(list 5120.3708 871.6333) 
(list 5120.3535 871.6436) 
(list 5120.3384 871.6539) 
(list 5120.3261 871.6642) 
(list 5120.317 871.6744) 
(list 5120.3113 871.6847) 
(list 5120.3093 871.695) 
(list 5120.3109 871.7053) 
(list 5120.3162 871.7156) 
(list 5120.325 871.7258) 
(list 5120.3371 871.7361) 
(list 5120.3522 871.7464) 
(list 5120.3697 871.7567) 
(list 5120.3891 871.7669) 
(list 5120.4099 871.7772) 
(list 5120.4315 871.7875) 
(list 5120.4531 871.7978) 
(list 5120.4742 871.8081) 
(list 5120.4941 871.8183) 
(list 5120.5121 871.8286) 
(list 5120.5278 871.8389) 
(list 5120.5406 871.8492) 
(list 5120.5501 871.8594) 
(list 5120.5561 871.8697) 
(list 5120.5583 871.88) 
(list 5120.5583 871.88)))
(apply 'command (append '("pline") coords '("c")))
(setq tap16 (ssadd (entlast) tap16))
(command "_mirror" (entlast) "" "5120,900" "5120,901" "No")
(setq tap16 (ssadd (entlast) tap16))
(setq coords (list 
(list 5121.137 871.51) 
(list 5120.5583 871.51) 
(list 5120.5583 871.5203) 
(list 5120.5583 871.5306) 
(list 5120.5583 871.5408) 
(list 5120.5583 871.5511) 
(list 5120.5583 871.5614) 
(list 5120.5583 871.5717) 
(list 5120.5583 871.5819) 
(list 5120.5583 871.5922) 
(list 5120.5583 871.6025) 
(list 5120.5583 871.6128) 
(list 5120.5583 871.6231) 
(list 5120.5583 871.6333) 
(list 5120.5583 871.6436) 
(list 5120.5583 871.6539) 
(list 5120.5583 871.6642) 
(list 5120.5583 871.6744) 
(list 5120.5583 871.6847) 
(list 5120.5583 871.695) 
(list 5120.5583 871.7053) 
(list 5120.5583 871.7156) 
(list 5120.5583 871.7258) 
(list 5120.5583 871.7361) 
(list 5120.5583 871.7464) 
(list 5120.5583 871.7567) 
(list 5120.5583 871.7669) 
(list 5120.5583 871.7772) 
(list 5120.5583 871.7875) 
(list 5120.5583 871.7978) 
(list 5120.5583 871.8081) 
(list 5120.5583 871.8183) 
(list 5120.5583 871.8286) 
(list 5120.5583 871.8389) 
(list 5120.5583 871.8492) 
(list 5120.5583 871.8594) 
(list 5120.5583 871.8697) 
(list 5120.5583 871.88) 
(list 5121.137 871.88)))
(apply 'command (append '("pline") coords '("c")))
(setq tap16 (ssadd (entlast) tap16))
(command "_mirror" (entlast) "" "5120,900" "5120,901" "No")
(setq tap16 (ssadd (entlast) tap16))
(setq coords (list 
(list 5120 871.88) 
(list 5120.135 871.88) 
(list 5120.135 871.8903) 
(list 5120.135 871.9006) 
(list 5120.135 871.9108) 
(list 5120.135 871.9211) 
(list 5120.135 871.9314) 
(list 5120.135 871.9417) 
(list 5120.135 871.9519) 
(list 5120.135 871.9622) 
(list 5120.135 871.9725) 
(list 5120.135 871.9828) 
(list 5120.135 871.9931) 
(list 5120.135 872.0033) 
(list 5120.135 872.0136) 
(list 5120.135 872.0239) 
(list 5120.135 872.0342) 
(list 5120.135 872.0444) 
(list 5120.135 872.0547) 
(list 5120.135 872.065) 
(list 5120.135 872.0753) 
(list 5120.135 872.0856) 
(list 5120.135 872.0958) 
(list 5120.135 872.1061) 
(list 5120.135 872.1164) 
(list 5120.135 872.1267) 
(list 5120.135 872.1369) 
(list 5120.135 872.1472) 
(list 5120.135 872.1575) 
(list 5120.135 872.1678) 
(list 5120.135 872.1781) 
(list 5120.135 872.1883) 
(list 5120.135 872.1986) 
(list 5120.135 872.2089) 
(list 5120.135 872.2192) 
(list 5120.135 872.2294) 
(list 5120.135 872.2397) 
(list 5120.135 872.25) 
(list 5120 872.25)))
(apply 'command (append '("pline") coords '("c")))
(setq tap16 (ssadd (entlast) tap16))
(command "_mirror" (entlast) "" "5120,900" "5120,901" "No")
(setq tap16 (ssadd (entlast) tap16))
(setq coords (list 
(list 5120.5685 871.88) 
(list 5120.5583 871.88) 
(list 5120.5566 871.8903) 
(list 5120.5512 871.9006) 
(list 5120.5421 871.9108) 
(list 5120.5296 871.9211) 
(list 5120.5141 871.9314) 
(list 5120.496 871.9417) 
(list 5120.4759 871.9519) 
(list 5120.4544 871.9622) 
(list 5120.4321 871.9725) 
(list 5120.4097 871.9828) 
(list 5120.388 871.9931) 
(list 5120.3675 872.0033) 
(list 5120.3488 872.0136) 
(list 5120.3327 872.0239) 
(list 5120.3195 872.0342) 
(list 5120.3097 872.0444) 
(list 5120.3036 872.0547) 
(list 5120.3014 872.065) 
(list 5120.3032 872.0753) 
(list 5120.3089 872.0856) 
(list 5120.3184 872.0958) 
(list 5120.3314 872.1061) 
(list 5120.3476 872.1164) 
(list 5120.3664 872.1267) 
(list 5120.3872 872.1369) 
(list 5120.4096 872.1472) 
(list 5120.4327 872.1575) 
(list 5120.4559 872.1678) 
(list 5120.4785 872.1781) 
(list 5120.4998 872.1883) 
(list 5120.5191 872.1986) 
(list 5120.5359 872.2089) 
(list 5120.5496 872.2192) 
(list 5120.5598 872.2294) 
(list 5120.5662 872.2397) 
(list 5120.5685 872.25) 
(list 5120.5685 872.25)))
(apply 'command (append '("pline") coords '("c")))
(setq tap16 (ssadd (entlast) tap16))
(command "_mirror" (entlast) "" "5120,900" "5120,901" "No")
(setq tap16 (ssadd (entlast) tap16))
(setq coords (list 
(list 5121.137 871.88) 
(list 5120.5685 871.88) 
(list 5120.5685 871.8903) 
(list 5120.5685 871.9006) 
(list 5120.5685 871.9108) 
(list 5120.5685 871.9211) 
(list 5120.5685 871.9314) 
(list 5120.5685 871.9417) 
(list 5120.5685 871.9519) 
(list 5120.5685 871.9622) 
(list 5120.5685 871.9725) 
(list 5120.5685 871.9828) 
(list 5120.5685 871.9931) 
(list 5120.5685 872.0033) 
(list 5120.5685 872.0136) 
(list 5120.5685 872.0239) 
(list 5120.5685 872.0342) 
(list 5120.5685 872.0444) 
(list 5120.5685 872.0547) 
(list 5120.5685 872.065) 
(list 5120.5685 872.0753) 
(list 5120.5685 872.0856) 
(list 5120.5685 872.0958) 
(list 5120.5685 872.1061) 
(list 5120.5685 872.1164) 
(list 5120.5685 872.1267) 
(list 5120.5685 872.1369) 
(list 5120.5685 872.1472) 
(list 5120.5685 872.1575) 
(list 5120.5685 872.1678) 
(list 5120.5685 872.1781) 
(list 5120.5685 872.1883) 
(list 5120.5685 872.1986) 
(list 5120.5685 872.2089) 
(list 5120.5685 872.2192) 
(list 5120.5685 872.2294) 
(list 5120.5685 872.2397) 
(list 5120.5685 872.25) 
(list 5121.137 872.25)))
(apply 'command (append '("pline") coords '("c")))
(setq tap16 (ssadd (entlast) tap16))
(command "_mirror" (entlast) "" "5120,900" "5120,901" "No")
(setq tap16 (ssadd (entlast) tap16))
(command "_block" "blktap16" "5120,900" tap16 "")
(command "_insert" "blktap16" "5120,900" "1" "1" "0")
(command "_insert" "blktap16" "5120,900" "1" "1" "180")
(setq uc16 nil)
(setq uc16 (ssadd))
(setq coords (list 
(list 0 -0.185) 
(list 0.135 -0.185) 
(list 0.135 -0.17472) 
(list 0.135 -0.16444) 
(list 0.135 -0.15417) 
(list 0.135 -0.14389) 
(list 0.135 -0.13361) 
(list 0.135 -0.12333) 
(list 0.135 -0.11306) 
(list 0.135 -0.10278) 
(list 0.135 -0.0925) 
(list 0.135 -0.082222) 
(list 0.135 -0.071944) 
(list 0.135 -0.061667) 
(list 0.135 -0.051389) 
(list 0.135 -0.041111) 
(list 0.135 -0.030833) 
(list 0.135 -0.020556) 
(list 0.135 -0.010278) 
(list 0.135 0) 
(list 0.135 0.010278) 
(list 0.135 0.020556) 
(list 0.135 0.030833) 
(list 0.135 0.041111) 
(list 0.135 0.051389) 
(list 0.135 0.061667) 
(list 0.135 0.071944) 
(list 0.135 0.082222) 
(list 0.135 0.0925) 
(list 0.135 0.10278) 
(list 0.135 0.11306) 
(list 0.135 0.12333) 
(list 0.135 0.13361) 
(list 0.135 0.14389) 
(list 0.135 0.15417) 
(list 0.135 0.16444) 
(list 0.135 0.17472) 
(list 0.135 0.185) 
(list 0 0.185)))
(apply 'command (append '("pline") coords '("c")))
(setq uc16 (ssadd (entlast) uc16))
(setq coords (list 
(list 1.137 -0.185) 
(list 0.5685 -0.185) 
(list 0.56644 -0.17472) 
(list 0.56033 -0.16444) 
(list 0.55035 -0.15417) 
(list 0.5368 -0.14389) 
(list 0.5201 -0.13361) 
(list 0.50075 -0.12333) 
(list 0.47934 -0.11306) 
(list 0.45653 -0.10278) 
(list 0.433 -0.0925) 
(list 0.40947 -0.082222) 
(list 0.38666 -0.071944) 
(list 0.36525 -0.061667) 
(list 0.3459 -0.051389) 
(list 0.3292 -0.041111) 
(list 0.31565 -0.030833) 
(list 0.30567 -0.020556) 
(list 0.29956 -0.010278) 
(list 0.2975 0) 
(list 0.29956 0.010278) 
(list 0.30567 0.020556) 
(list 0.31565 0.030833) 
(list 0.3292 0.041111) 
(list 0.3459 0.051389) 
(list 0.36525 0.061667) 
(list 0.38666 0.071944) 
(list 0.40947 0.082222) 
(list 0.433 0.0925) 
(list 0.45653 0.10278) 
(list 0.47934 0.11306) 
(list 0.50075 0.12333) 
(list 0.5201 0.13361) 
(list 0.5368 0.14389) 
(list 0.55035 0.15417) 
(list 0.56033 0.16444) 
(list 0.56644 0.17472) 
(list 0.5685 0.185) 
(list 1.137 0.185)))
(apply 'command (append '("pline") coords '("c")))
(setq uc16 (ssadd (entlast) uc16))
(command "_block" "blkuc16" "0,0.185" uc16 "")
(command "_insert" "blkuc16" "5120,872.62" "1" "1" "0")
(command "_insert" "blkuc16" "5120,872.25" "1" "1" "180")
(command "_insert" "blkuc16" "5120,872.99" "1" "1" "0")
(command "_insert" "blkuc16" "5120,872.62" "1" "1" "180")
(command "_insert" "blkuc16" "5120,873.36" "1" "1" "0")
(command "_insert" "blkuc16" "5120,872.99" "1" "1" "180")
(command "_insert" "blkuc16" "5120,873.73" "1" "1" "0")
(command "_insert" "blkuc16" "5120,873.36" "1" "1" "180")
(command "_insert" "blkuc16" "5120,874.1" "1" "1" "0")
(command "_insert" "blkuc16" "5120,873.73" "1" "1" "180")
(command "_insert" "blkuc16" "5120,874.47" "1" "1" "0")
(command "_insert" "blkuc16" "5120,874.1" "1" "1" "180")
(command "_insert" "blkuc16" "5120,874.84" "1" "1" "0")
(command "_insert" "blkuc16" "5120,874.47" "1" "1" "180")
(command "_insert" "blkuc16" "5120,875.21" "1" "1" "0")
(command "_insert" "blkuc16" "5120,874.84" "1" "1" "180")
(command "_insert" "blkuc16" "5120,875.58" "1" "1" "0")
(command "_insert" "blkuc16" "5120,875.21" "1" "1" "180")
(command "_insert" "blkuc16" "5120,875.95" "1" "1" "0")
(command "_insert" "blkuc16" "5120,875.58" "1" "1" "180")
(command "_insert" "blkuc16" "5120,876.32" "1" "1" "0")
(command "_insert" "blkuc16" "5120,875.95" "1" "1" "180")
(command "_insert" "blkuc16" "5120,876.69" "1" "1" "0")
(command "_insert" "blkuc16" "5120,876.32" "1" "1" "180")
(command "_insert" "blkuc16" "5120,877.06" "1" "1" "0")
(command "_insert" "blkuc16" "5120,876.69" "1" "1" "180")
(command "_insert" "blkuc16" "5120,877.43" "1" "1" "0")
(command "_insert" "blkuc16" "5120,877.06" "1" "1" "180")
(command "_insert" "blkuc16" "5120,877.8" "1" "1" "0")
(command "_insert" "blkuc16" "5120,877.43" "1" "1" "180")
(command "_insert" "blkuc16" "5120,878.17" "1" "1" "0")
(command "_insert" "blkuc16" "5120,877.8" "1" "1" "180")
(command "_insert" "blkuc16" "5120,878.54" "1" "1" "0")
(command "_insert" "blkuc16" "5120,878.17" "1" "1" "180")
(command "_insert" "blkuc16" "5120,878.91" "1" "1" "0")
(command "_insert" "blkuc16" "5120,878.54" "1" "1" "180")
(command "_insert" "blkuc16" "5120,879.28" "1" "1" "0")
(command "_insert" "blkuc16" "5120,878.91" "1" "1" "180")
(command "_insert" "blkuc16" "5120,879.65" "1" "1" "0")
(command "_insert" "blkuc16" "5120,879.28" "1" "1" "180")
(command "_insert" "blkuc16" "5120,880.02" "1" "1" "0")
(command "_insert" "blkuc16" "5120,879.65" "1" "1" "180")
(command "_insert" "blkuc16" "5120,880.39" "1" "1" "0")
(command "_insert" "blkuc16" "5120,880.02" "1" "1" "180")
(command "_insert" "blkuc16" "5120,880.76" "1" "1" "0")
(command "_insert" "blkuc16" "5120,880.39" "1" "1" "180")
(command "_insert" "blkuc16" "5120,881.13" "1" "1" "0")
(command "_insert" "blkuc16" "5120,880.76" "1" "1" "180")
(command "_insert" "blkuc16" "5120,881.5" "1" "1" "0")
(command "_insert" "blkuc16" "5120,881.13" "1" "1" "180")
(command "_insert" "blkuc16" "5120,881.87" "1" "1" "0")
(command "_insert" "blkuc16" "5120,881.5" "1" "1" "180")
(command "_insert" "blkuc16" "5120,882.24" "1" "1" "0")
(command "_insert" "blkuc16" "5120,881.87" "1" "1" "180")
(command "_insert" "blkuc16" "5120,882.61" "1" "1" "0")
(command "_insert" "blkuc16" "5120,882.24" "1" "1" "180")
(command "_insert" "blkuc16" "5120,882.98" "1" "1" "0")
(command "_insert" "blkuc16" "5120,882.61" "1" "1" "180")
(command "_insert" "blkuc16" "5120,883.35" "1" "1" "0")
(command "_insert" "blkuc16" "5120,882.98" "1" "1" "180")
(command "_insert" "blkuc16" "5120,883.72" "1" "1" "0")
(command "_insert" "blkuc16" "5120,883.35" "1" "1" "180")
(command "_insert" "blkuc16" "5120,884.09" "1" "1" "0")
(command "_insert" "blkuc16" "5120,883.72" "1" "1" "180")
(command "_insert" "blkuc16" "5120,884.46" "1" "1" "0")
(command "_insert" "blkuc16" "5120,884.09" "1" "1" "180")
(command "_insert" "blkuc16" "5120,884.83" "1" "1" "0")
(command "_insert" "blkuc16" "5120,884.46" "1" "1" "180")
(command "_insert" "blkuc16" "5120,885.2" "1" "1" "0")
(command "_insert" "blkuc16" "5120,884.83" "1" "1" "180")
(command "_insert" "blkuc16" "5120,885.57" "1" "1" "0")
(command "_insert" "blkuc16" "5120,885.2" "1" "1" "180")
(command "_insert" "blkuc16" "5120,885.94" "1" "1" "0")
(command "_insert" "blkuc16" "5120,885.57" "1" "1" "180")
(command "_insert" "blkuc16" "5120,886.31" "1" "1" "0")
(command "_insert" "blkuc16" "5120,885.94" "1" "1" "180")
(command "_insert" "blkuc16" "5120,886.68" "1" "1" "0")
(command "_insert" "blkuc16" "5120,886.31" "1" "1" "180")
(command "_insert" "blkuc16" "5120,887.05" "1" "1" "0")
(command "_insert" "blkuc16" "5120,886.68" "1" "1" "180")
(command "_insert" "blkuc16" "5120,887.42" "1" "1" "0")
(command "_insert" "blkuc16" "5120,887.05" "1" "1" "180")
(command "_insert" "blkuc16" "5120,887.79" "1" "1" "0")
(command "_insert" "blkuc16" "5120,887.42" "1" "1" "180")
(command "_insert" "blkuc16" "5120,888.16" "1" "1" "0")
(command "_insert" "blkuc16" "5120,887.79" "1" "1" "180")
(command "_insert" "blkuc16" "5120,888.53" "1" "1" "0")
(command "_insert" "blkuc16" "5120,888.16" "1" "1" "180")
(command "_insert" "blkuc16" "5120,888.9" "1" "1" "0")
(command "_insert" "blkuc16" "5120,888.53" "1" "1" "180")
(command "_insert" "blkuc16" "5120,889.27" "1" "1" "0")
(command "_insert" "blkuc16" "5120,888.9" "1" "1" "180")
(command "_insert" "blkuc16" "5120,889.64" "1" "1" "0")
(command "_insert" "blkuc16" "5120,889.27" "1" "1" "180")
(command "_insert" "blkuc16" "5120,890.01" "1" "1" "0")
(command "_insert" "blkuc16" "5120,889.64" "1" "1" "180")
(command "_insert" "blkuc16" "5120,890.38" "1" "1" "0")
(command "_insert" "blkuc16" "5120,890.01" "1" "1" "180")
(command "_insert" "blkuc16" "5120,890.75" "1" "1" "0")
(command "_insert" "blkuc16" "5120,890.38" "1" "1" "180")
(command "_insert" "blkuc16" "5120,891.12" "1" "1" "0")
(command "_insert" "blkuc16" "5120,890.75" "1" "1" "180")
(command "_insert" "blkuc16" "5120,891.49" "1" "1" "0")
(command "_insert" "blkuc16" "5120,891.12" "1" "1" "180")
(command "_insert" "blkuc16" "5120,891.86" "1" "1" "0")
(command "_insert" "blkuc16" "5120,891.49" "1" "1" "180")
(command "_insert" "blkuc16" "5120,892.23" "1" "1" "0")
(command "_insert" "blkuc16" "5120,891.86" "1" "1" "180")
(command "_insert" "blkuc16" "5120,892.6" "1" "1" "0")
(command "_insert" "blkuc16" "5120,892.23" "1" "1" "180")
(command "_insert" "blkuc16" "5120,892.97" "1" "1" "0")
(command "_insert" "blkuc16" "5120,892.6" "1" "1" "180")
(command "_insert" "blkuc16" "5120,893.34" "1" "1" "0")
(command "_insert" "blkuc16" "5120,892.97" "1" "1" "180")
(command "_insert" "blkuc16" "5120,893.71" "1" "1" "0")
(command "_insert" "blkuc16" "5120,893.34" "1" "1" "180")
(command "_insert" "blkuc16" "5120,894.08" "1" "1" "0")
(command "_insert" "blkuc16" "5120,893.71" "1" "1" "180")
(command "_insert" "blkuc16" "5120,894.45" "1" "1" "0")
(command "_insert" "blkuc16" "5120,894.08" "1" "1" "180")
(command "_insert" "blkuc16" "5120,894.82" "1" "1" "0")
(command "_insert" "blkuc16" "5120,894.45" "1" "1" "180")
(command "_insert" "blkuc16" "5120,895.19" "1" "1" "0")
(command "_insert" "blkuc16" "5120,894.82" "1" "1" "180")
(command "_insert" "blkuc16" "5120,895.56" "1" "1" "0")
(command "_insert" "blkuc16" "5120,895.19" "1" "1" "180")
(command "_insert" "blkuc16" "5120,895.93" "1" "1" "0")
(command "_insert" "blkuc16" "5120,895.56" "1" "1" "180")
(command "_insert" "blkuc16" "5120,896.3" "1" "1" "0")
(command "_insert" "blkuc16" "5120,895.93" "1" "1" "180")
(command "_insert" "blkuc16" "5120,896.67" "1" "1" "0")
(command "_insert" "blkuc16" "5120,896.3" "1" "1" "180")
(command "_insert" "blkuc16" "5120,897.04" "1" "1" "0")
(command "_insert" "blkuc16" "5120,896.67" "1" "1" "180")
(command "_insert" "blkuc16" "5120,897.41" "1" "1" "0")
(command "_insert" "blkuc16" "5120,897.04" "1" "1" "180")
(command "_insert" "blkuc16" "5120,897.78" "1" "1" "0")
(command "_insert" "blkuc16" "5120,897.41" "1" "1" "180")
(command "_insert" "blkuc16" "5120,898.15" "1" "1" "0")
(command "_insert" "blkuc16" "5120,897.78" "1" "1" "180")
(command "_insert" "blkuc16" "5120,898.52" "1" "1" "0")
(command "_insert" "blkuc16" "5120,898.15" "1" "1" "180")
(command "_insert" "blkuc16" "5120,898.89" "1" "1" "0")
(command "_insert" "blkuc16" "5120,898.52" "1" "1" "180")
(command "_insert" "blkuc16" "5120,899.26" "1" "1" "0")
(command "_insert" "blkuc16" "5120,898.89" "1" "1" "180")
(command "_insert" "blkuc16" "5120,899.63" "1" "1" "0")
(command "_insert" "blkuc16" "5120,899.26" "1" "1" "180")
(command "_insert" "blkuc16" "5120,900" "1" "1" "0")
(command "_insert" "blkuc16" "5120,899.63" "1" "1" "180")
(command "_insert" "blkuc16" "5120,900.37" "1" "1" "0")
(command "_insert" "blkuc16" "5120,900" "1" "1" "180")
(command "_insert" "blkuc16" "5120,900.74" "1" "1" "0")
(command "_insert" "blkuc16" "5120,900.37" "1" "1" "180")
(command "_insert" "blkuc16" "5120,901.11" "1" "1" "0")
(command "_insert" "blkuc16" "5120,900.74" "1" "1" "180")
(command "_insert" "blkuc16" "5120,901.48" "1" "1" "0")
(command "_insert" "blkuc16" "5120,901.11" "1" "1" "180")
(command "_insert" "blkuc16" "5120,901.85" "1" "1" "0")
(command "_insert" "blkuc16" "5120,901.48" "1" "1" "180")
(command "_insert" "blkuc16" "5120,902.22" "1" "1" "0")
(command "_insert" "blkuc16" "5120,901.85" "1" "1" "180")
(command "_insert" "blkuc16" "5120,902.59" "1" "1" "0")
(command "_insert" "blkuc16" "5120,902.22" "1" "1" "180")
(command "_insert" "blkuc16" "5120,902.96" "1" "1" "0")
(command "_insert" "blkuc16" "5120,902.59" "1" "1" "180")
(command "_insert" "blkuc16" "5120,903.33" "1" "1" "0")
(command "_insert" "blkuc16" "5120,902.96" "1" "1" "180")
(command "_insert" "blkuc16" "5120,903.7" "1" "1" "0")
(command "_insert" "blkuc16" "5120,903.33" "1" "1" "180")
(command "_insert" "blkuc16" "5120,904.07" "1" "1" "0")
(command "_insert" "blkuc16" "5120,903.7" "1" "1" "180")
(command "_insert" "blkuc16" "5120,904.44" "1" "1" "0")
(command "_insert" "blkuc16" "5120,904.07" "1" "1" "180")
(command "_insert" "blkuc16" "5120,904.81" "1" "1" "0")
(command "_insert" "blkuc16" "5120,904.44" "1" "1" "180")
(command "_insert" "blkuc16" "5120,905.18" "1" "1" "0")
(command "_insert" "blkuc16" "5120,904.81" "1" "1" "180")
(command "_insert" "blkuc16" "5120,905.55" "1" "1" "0")
(command "_insert" "blkuc16" "5120,905.18" "1" "1" "180")
(command "_insert" "blkuc16" "5120,905.92" "1" "1" "0")
(command "_insert" "blkuc16" "5120,905.55" "1" "1" "180")
(command "_insert" "blkuc16" "5120,906.29" "1" "1" "0")
(command "_insert" "blkuc16" "5120,905.92" "1" "1" "180")
(command "_insert" "blkuc16" "5120,906.66" "1" "1" "0")
(command "_insert" "blkuc16" "5120,906.29" "1" "1" "180")
(command "_insert" "blkuc16" "5120,907.03" "1" "1" "0")
(command "_insert" "blkuc16" "5120,906.66" "1" "1" "180")
(command "_insert" "blkuc16" "5120,907.4" "1" "1" "0")
(command "_insert" "blkuc16" "5120,907.03" "1" "1" "180")
(command "_insert" "blkuc16" "5120,907.77" "1" "1" "0")
(command "_insert" "blkuc16" "5120,907.4" "1" "1" "180")
(command "_insert" "blkuc16" "5120,908.14" "1" "1" "0")
(command "_insert" "blkuc16" "5120,907.77" "1" "1" "180")
(command "_insert" "blkuc16" "5120,908.51" "1" "1" "0")
(command "_insert" "blkuc16" "5120,908.14" "1" "1" "180")
(command "_insert" "blkuc16" "5120,908.88" "1" "1" "0")
(command "_insert" "blkuc16" "5120,908.51" "1" "1" "180")
(command "_insert" "blkuc16" "5120,909.25" "1" "1" "0")
(command "_insert" "blkuc16" "5120,908.88" "1" "1" "180")
(command "_insert" "blkuc16" "5120,909.62" "1" "1" "0")
(command "_insert" "blkuc16" "5120,909.25" "1" "1" "180")
(command "_insert" "blkuc16" "5120,909.99" "1" "1" "0")
(command "_insert" "blkuc16" "5120,909.62" "1" "1" "180")
(command "_insert" "blkuc16" "5120,910.36" "1" "1" "0")
(command "_insert" "blkuc16" "5120,909.99" "1" "1" "180")
(command "_insert" "blkuc16" "5120,910.73" "1" "1" "0")
(command "_insert" "blkuc16" "5120,910.36" "1" "1" "180")
(command "_insert" "blkuc16" "5120,911.1" "1" "1" "0")
(command "_insert" "blkuc16" "5120,910.73" "1" "1" "180")
(command "_insert" "blkuc16" "5120,911.47" "1" "1" "0")
(command "_insert" "blkuc16" "5120,911.1" "1" "1" "180")
(command "_insert" "blkuc16" "5120,911.84" "1" "1" "0")
(command "_insert" "blkuc16" "5120,911.47" "1" "1" "180")
(command "_insert" "blkuc16" "5120,912.21" "1" "1" "0")
(command "_insert" "blkuc16" "5120,911.84" "1" "1" "180")
(command "_insert" "blkuc16" "5120,912.58" "1" "1" "0")
(command "_insert" "blkuc16" "5120,912.21" "1" "1" "180")
(command "_insert" "blkuc16" "5120,912.95" "1" "1" "0")
(command "_insert" "blkuc16" "5120,912.58" "1" "1" "180")
(command "_insert" "blkuc16" "5120,913.32" "1" "1" "0")
(command "_insert" "blkuc16" "5120,912.95" "1" "1" "180")
(command "_insert" "blkuc16" "5120,913.69" "1" "1" "0")
(command "_insert" "blkuc16" "5120,913.32" "1" "1" "180")
(command "_insert" "blkuc16" "5120,914.06" "1" "1" "0")
(command "_insert" "blkuc16" "5120,913.69" "1" "1" "180")
(command "_insert" "blkuc16" "5120,914.43" "1" "1" "0")
(command "_insert" "blkuc16" "5120,914.06" "1" "1" "180")
(command "_insert" "blkuc16" "5120,914.8" "1" "1" "0")
(command "_insert" "blkuc16" "5120,914.43" "1" "1" "180")
(command "_insert" "blkuc16" "5120,915.17" "1" "1" "0")
(command "_insert" "blkuc16" "5120,914.8" "1" "1" "180")
(command "_insert" "blkuc16" "5120,915.54" "1" "1" "0")
(command "_insert" "blkuc16" "5120,915.17" "1" "1" "180")
(command "_insert" "blkuc16" "5120,915.91" "1" "1" "0")
(command "_insert" "blkuc16" "5120,915.54" "1" "1" "180")
(command "_insert" "blkuc16" "5120,916.28" "1" "1" "0")
(command "_insert" "blkuc16" "5120,915.91" "1" "1" "180")
(command "_insert" "blkuc16" "5120,916.65" "1" "1" "0")
(command "_insert" "blkuc16" "5120,916.28" "1" "1" "180")
(command "_insert" "blkuc16" "5120,917.02" "1" "1" "0")
(command "_insert" "blkuc16" "5120,916.65" "1" "1" "180")
(command "_insert" "blkuc16" "5120,917.39" "1" "1" "0")
(command "_insert" "blkuc16" "5120,917.02" "1" "1" "180")
(command "_insert" "blkuc16" "5120,917.76" "1" "1" "0")
(command "_insert" "blkuc16" "5120,917.39" "1" "1" "180")
(command "_insert" "blkuc16" "5120,918.13" "1" "1" "0")
(command "_insert" "blkuc16" "5120,917.76" "1" "1" "180")
(command "_insert" "blkuc16" "5120,918.5" "1" "1" "0")
(command "_insert" "blkuc16" "5120,918.13" "1" "1" "180")
(command "_insert" "blkuc16" "5120,918.87" "1" "1" "0")
(command "_insert" "blkuc16" "5120,918.5" "1" "1" "180")
(command "_insert" "blkuc16" "5120,919.24" "1" "1" "0")
(command "_insert" "blkuc16" "5120,918.87" "1" "1" "180")
(command "_insert" "blkuc16" "5120,919.61" "1" "1" "0")
(command "_insert" "blkuc16" "5120,919.24" "1" "1" "180")
(command "_insert" "blkuc16" "5120,919.98" "1" "1" "0")
(command "_insert" "blkuc16" "5120,919.61" "1" "1" "180")
(command "_insert" "blkuc16" "5120,920.35" "1" "1" "0")
(command "_insert" "blkuc16" "5120,919.98" "1" "1" "180")
(command "_insert" "blkuc16" "5120,920.72" "1" "1" "0")
(command "_insert" "blkuc16" "5120,920.35" "1" "1" "180")
(command "_insert" "blkuc16" "5120,921.09" "1" "1" "0")
(command "_insert" "blkuc16" "5120,920.72" "1" "1" "180")
(command "_insert" "blkuc16" "5120,921.46" "1" "1" "0")
(command "_insert" "blkuc16" "5120,921.09" "1" "1" "180")
(command "_insert" "blkuc16" "5120,921.83" "1" "1" "0")
(command "_insert" "blkuc16" "5120,921.46" "1" "1" "180")
(command "_insert" "blkuc16" "5120,922.2" "1" "1" "0")
(command "_insert" "blkuc16" "5120,921.83" "1" "1" "180")
(command "_insert" "blkuc16" "5120,922.57" "1" "1" "0")
(command "_insert" "blkuc16" "5120,922.2" "1" "1" "180")
(command "_insert" "blkuc16" "5120,922.94" "1" "1" "0")
(command "_insert" "blkuc16" "5120,922.57" "1" "1" "180")
(command "_insert" "blkuc16" "5120,923.31" "1" "1" "0")
(command "_insert" "blkuc16" "5120,922.94" "1" "1" "180")
(command "_insert" "blkuc16" "5120,923.68" "1" "1" "0")
(command "_insert" "blkuc16" "5120,923.31" "1" "1" "180")
(command "_insert" "blkuc16" "5120,924.05" "1" "1" "0")
(command "_insert" "blkuc16" "5120,923.68" "1" "1" "180")
(command "_insert" "blkuc16" "5120,924.42" "1" "1" "0")
(command "_insert" "blkuc16" "5120,924.05" "1" "1" "180")
(command "_insert" "blkuc16" "5120,924.79" "1" "1" "0")
(command "_insert" "blkuc16" "5120,924.42" "1" "1" "180")
(command "_insert" "blkuc16" "5120,925.16" "1" "1" "0")
(command "_insert" "blkuc16" "5120,924.79" "1" "1" "180")
(command "_insert" "blkuc16" "5120,925.53" "1" "1" "0")
(command "_insert" "blkuc16" "5120,925.16" "1" "1" "180")
(command "_insert" "blkuc16" "5120,925.9" "1" "1" "0")
(command "_insert" "blkuc16" "5120,925.53" "1" "1" "180")
(command "_insert" "blkuc16" "5120,926.27" "1" "1" "0")
(command "_insert" "blkuc16" "5120,925.9" "1" "1" "180")
(command "_insert" "blkuc16" "5120,926.64" "1" "1" "0")
(command "_insert" "blkuc16" "5120,926.27" "1" "1" "180")
(command "_insert" "blkuc16" "5120,927.01" "1" "1" "0")
(command "_insert" "blkuc16" "5120,926.64" "1" "1" "180")
(command "_insert" "blkuc16" "5120,927.38" "1" "1" "0")
(command "_insert" "blkuc16" "5120,927.01" "1" "1" "180")
(command "_insert" "blkuc16" "5120,927.75" "1" "1" "0")
(command "_insert" "blkuc16" "5120,927.38" "1" "1" "180")
(command "_layer" "set" "phccover" "")
(command "_rectangle" "5118.863,933.3" "5121.137,866.7")
(command "_layer" "set" "nitride" "")
(setq phc16 currobj)
(command "_layer" "set" "cover" "")
(command "_rectangle" "5118.863,836.7" "5121.137,963.3")
(command "_layer" "set" "nitride" "")
(command "_layer" "set" "text" "")
(command "_circle" "5117.913,846.7" "0.075")
(command "_circle" "5117.538,846.7" "0.15")
(command "_circle" "5117.163,846.7" "0.075")
(command "_circle" "5116.788,846.7" "0.15")
(command "_circle" "5117.913,848.7" "0.075")
(command "_circle" "5117.538,848.7" "0.075")
(command "_circle" "5117.163,848.7" "0.15")
(command "_circle" "5116.788,848.7" "0.15")
(command "_circle" "5117.913,850.7" "0.075")
(command "_circle" "5117.538,850.7" "0.15")
(command "_circle" "5117.163,850.7" "0.15")
(command "_circle" "5116.788,850.7" "0.15")
(command "_circle" "5117.913,852.7" "0.075")
(command "_circle" "5117.538,852.7" "0.075")
(command "_circle" "5117.163,852.7" "0.075")
(command "_circle" "5116.788,852.7" "0.075")
(command "_circle" "5116.413,852.7" "0.15")
(command "_circle" "5117.913,854.7" "0.075")
(command "_circle" "5117.538,854.7" "0.15")
(command "_circle" "5117.163,854.7" "0.075")
(command "_circle" "5116.788,854.7" "0.075")
(command "_circle" "5116.413,854.7" "0.15")
(command "_circle" "5117.913,856.7" "0.075")
(command "_circle" "5117.538,856.7" "0.075")
(command "_circle" "5117.163,856.7" "0.15")
(command "_circle" "5116.788,856.7" "0.075")
(command "_circle" "5116.413,856.7" "0.15")
(command "_circle" "5117.913,858.7" "0.075")
(command "_circle" "5117.538,858.7" "0.15")
(command "_circle" "5117.163,858.7" "0.15")
(command "_circle" "5116.788,858.7" "0.075")
(command "_circle" "5116.413,858.7" "0.15")
(command "_circle" "5117.913,860.7" "0.075")
(command "_circle" "5117.538,860.7" "0.075")
(command "_circle" "5117.163,860.7" "0.075")
(command "_circle" "5116.788,860.7" "0.15")
(command "_circle" "5116.413,860.7" "0.15")
(command "_circle" "5117.913,862.7" "0.075")
(command "_circle" "5117.538,862.7" "0.15")
(command "_circle" "5117.163,862.7" "0.075")
(command "_circle" "5116.788,862.7" "0.15")
(command "_circle" "5116.413,862.7" "0.15")
(command "_circle" "5117.913,864.7" "0.075")
(command "_circle" "5117.538,864.7" "0.075")
(command "_circle" "5117.163,864.7" "0.15")
(command "_circle" "5116.788,864.7" "0.15")
(command "_circle" "5116.413,864.7" "0.15")
(command "_circle" "5117.913,866.7" "0.075")
(command "_circle" "5117.538,866.7" "0.15")
(command "_circle" "5117.163,866.7" "0.15")
(command "_circle" "5116.788,866.7" "0.15")
(command "_circle" "5116.413,866.7" "0.15")
(command "_circle" "5117.913,868.7" "0.075")
(command "_circle" "5117.538,868.7" "0.075")
(command "_circle" "5117.163,868.7" "0.075")
(command "_circle" "5116.788,868.7" "0.075")
(command "_circle" "5116.413,868.7" "0.075")
(command "_circle" "5116.038,868.7" "0.15")
(command "_circle" "5117.913,870.7" "0.075")
(command "_circle" "5117.538,870.7" "0.15")
(command "_circle" "5117.163,870.7" "0.075")
(command "_circle" "5116.788,870.7" "0.075")
(command "_circle" "5116.413,870.7" "0.075")
(command "_circle" "5116.038,870.7" "0.15")
(command "_circle" "5117.913,872.7" "0.075")
(command "_circle" "5117.538,872.7" "0.075")
(command "_circle" "5117.163,872.7" "0.15")
(command "_circle" "5116.788,872.7" "0.075")
(command "_circle" "5116.413,872.7" "0.075")
(command "_circle" "5116.038,872.7" "0.15")
(command "_circle" "5117.913,874.7" "0.075")
(command "_circle" "5117.538,874.7" "0.15")
(command "_circle" "5117.163,874.7" "0.15")
(command "_circle" "5116.788,874.7" "0.075")
(command "_circle" "5116.413,874.7" "0.075")
(command "_circle" "5116.038,874.7" "0.15")
(command "_circle" "5117.913,876.7" "0.075")
(command "_circle" "5117.538,876.7" "0.075")
(command "_circle" "5117.163,876.7" "0.075")
(command "_circle" "5116.788,876.7" "0.15")
(command "_circle" "5116.413,876.7" "0.075")
(command "_circle" "5116.038,876.7" "0.15")
(command "_circle" "5117.913,878.7" "0.075")
(command "_circle" "5117.538,878.7" "0.15")
(command "_circle" "5117.163,878.7" "0.075")
(command "_circle" "5116.788,878.7" "0.15")
(command "_circle" "5116.413,878.7" "0.075")
(command "_circle" "5116.038,878.7" "0.15")
(command "_circle" "5117.913,880.7" "0.075")
(command "_circle" "5117.538,880.7" "0.075")
(command "_circle" "5117.163,880.7" "0.15")
(command "_circle" "5116.788,880.7" "0.15")
(command "_circle" "5116.413,880.7" "0.075")
(command "_circle" "5116.038,880.7" "0.15")
(command "_circle" "5117.913,882.7" "0.075")
(command "_circle" "5117.538,882.7" "0.15")
(command "_circle" "5117.163,882.7" "0.15")
(command "_circle" "5116.788,882.7" "0.15")
(command "_circle" "5116.413,882.7" "0.075")
(command "_circle" "5116.038,882.7" "0.15")
(command "_circle" "5117.913,884.7" "0.075")
(command "_circle" "5117.538,884.7" "0.075")
(command "_circle" "5117.163,884.7" "0.075")
(command "_circle" "5116.788,884.7" "0.075")
(command "_circle" "5116.413,884.7" "0.15")
(command "_circle" "5116.038,884.7" "0.15")
(command "_circle" "5117.913,886.7" "0.075")
(command "_circle" "5117.538,886.7" "0.15")
(command "_circle" "5117.163,886.7" "0.075")
(command "_circle" "5116.788,886.7" "0.075")
(command "_circle" "5116.413,886.7" "0.15")
(command "_circle" "5116.038,886.7" "0.15")
(command "_circle" "5117.913,888.7" "0.075")
(command "_circle" "5117.538,888.7" "0.075")
(command "_circle" "5117.163,888.7" "0.15")
(command "_circle" "5116.788,888.7" "0.075")
(command "_circle" "5116.413,888.7" "0.15")
(command "_circle" "5116.038,888.7" "0.15")
(command "_circle" "5117.913,890.7" "0.075")
(command "_circle" "5117.538,890.7" "0.15")
(command "_circle" "5117.163,890.7" "0.15")
(command "_circle" "5116.788,890.7" "0.075")
(command "_circle" "5116.413,890.7" "0.15")
(command "_circle" "5116.038,890.7" "0.15")
(command "_circle" "5117.913,892.7" "0.075")
(command "_circle" "5117.538,892.7" "0.075")
(command "_circle" "5117.163,892.7" "0.075")
(command "_circle" "5116.788,892.7" "0.15")
(command "_circle" "5116.413,892.7" "0.15")
(command "_circle" "5116.038,892.7" "0.15")
(command "_circle" "5117.913,894.7" "0.075")
(command "_circle" "5117.538,894.7" "0.15")
(command "_circle" "5117.163,894.7" "0.075")
(command "_circle" "5116.788,894.7" "0.15")
(command "_circle" "5116.413,894.7" "0.15")
(command "_circle" "5116.038,894.7" "0.15")
(command "_circle" "5117.913,896.7" "0.075")
(command "_circle" "5117.538,896.7" "0.075")
(command "_circle" "5117.163,896.7" "0.15")
(command "_circle" "5116.788,896.7" "0.15")
(command "_circle" "5116.413,896.7" "0.15")
(command "_circle" "5116.038,896.7" "0.15")
(command "_circle" "5117.913,898.7" "0.075")
(command "_circle" "5117.538,898.7" "0.15")
(command "_circle" "5117.163,898.7" "0.15")
(command "_circle" "5116.788,898.7" "0.15")
(command "_circle" "5116.413,898.7" "0.15")
(command "_circle" "5116.038,898.7" "0.15")
(command "_circle" "5117.913,900.7" "0.075")
(command "_circle" "5117.538,900.7" "0.075")
(command "_circle" "5117.163,900.7" "0.075")
(command "_circle" "5116.788,900.7" "0.075")
(command "_circle" "5116.413,900.7" "0.075")
(command "_circle" "5116.038,900.7" "0.075")
(command "_circle" "5115.663,900.7" "0.15")
(command "_circle" "5117.913,902.7" "0.075")
(command "_circle" "5117.538,902.7" "0.15")
(command "_circle" "5117.163,902.7" "0.075")
(command "_circle" "5116.788,902.7" "0.075")
(command "_circle" "5116.413,902.7" "0.075")
(command "_circle" "5116.038,902.7" "0.075")
(command "_circle" "5115.663,902.7" "0.15")
(command "_circle" "5117.913,904.7" "0.075")
(command "_circle" "5117.538,904.7" "0.075")
(command "_circle" "5117.163,904.7" "0.15")
(command "_circle" "5116.788,904.7" "0.075")
(command "_circle" "5116.413,904.7" "0.075")
(command "_circle" "5116.038,904.7" "0.075")
(command "_circle" "5115.663,904.7" "0.15")
(command "_circle" "5117.913,906.7" "0.075")
(command "_circle" "5117.538,906.7" "0.15")
(command "_circle" "5117.163,906.7" "0.15")
(command "_circle" "5116.788,906.7" "0.075")
(command "_circle" "5116.413,906.7" "0.075")
(command "_circle" "5116.038,906.7" "0.075")
(command "_circle" "5115.663,906.7" "0.15")
(command "_circle" "5117.913,908.7" "0.075")
(command "_circle" "5117.538,908.7" "0.075")
(command "_circle" "5117.163,908.7" "0.075")
(command "_circle" "5116.788,908.7" "0.15")
(command "_circle" "5116.413,908.7" "0.075")
(command "_circle" "5116.038,908.7" "0.075")
(command "_circle" "5115.663,908.7" "0.15")
(command "_circle" "5117.913,910.7" "0.075")
(command "_circle" "5117.538,910.7" "0.15")
(command "_circle" "5117.163,910.7" "0.075")
(command "_circle" "5116.788,910.7" "0.15")
(command "_circle" "5116.413,910.7" "0.075")
(command "_circle" "5116.038,910.7" "0.075")
(command "_circle" "5115.663,910.7" "0.15")
(command "_circle" "5117.913,912.7" "0.075")
(command "_circle" "5117.538,912.7" "0.075")
(command "_circle" "5117.163,912.7" "0.15")
(command "_circle" "5116.788,912.7" "0.15")
(command "_circle" "5116.413,912.7" "0.075")
(command "_circle" "5116.038,912.7" "0.075")
(command "_circle" "5115.663,912.7" "0.15")
(command "_circle" "5117.913,914.7" "0.075")
(command "_circle" "5117.538,914.7" "0.15")
(command "_circle" "5117.163,914.7" "0.15")
(command "_circle" "5116.788,914.7" "0.15")
(command "_circle" "5116.413,914.7" "0.075")
(command "_circle" "5116.038,914.7" "0.075")
(command "_circle" "5115.663,914.7" "0.15")
(command "_circle" "5117.913,916.7" "0.075")
(command "_circle" "5117.538,916.7" "0.075")
(command "_circle" "5117.163,916.7" "0.075")
(command "_circle" "5116.788,916.7" "0.075")
(command "_circle" "5116.413,916.7" "0.15")
(command "_circle" "5116.038,916.7" "0.075")
(command "_circle" "5115.663,916.7" "0.15")
(command "_circle" "5117.913,918.7" "0.075")
(command "_circle" "5117.538,918.7" "0.15")
(command "_circle" "5117.163,918.7" "0.075")
(command "_circle" "5116.788,918.7" "0.075")
(command "_circle" "5116.413,918.7" "0.15")
(command "_circle" "5116.038,918.7" "0.075")
(command "_circle" "5115.663,918.7" "0.15")
(command "_circle" "5117.913,920.7" "0.075")
(command "_circle" "5117.538,920.7" "0.075")
(command "_circle" "5117.163,920.7" "0.15")
(command "_circle" "5116.788,920.7" "0.075")
(command "_circle" "5116.413,920.7" "0.15")
(command "_circle" "5116.038,920.7" "0.075")
(command "_circle" "5115.663,920.7" "0.15")
(command "_circle" "5117.913,922.7" "0.075")
(command "_circle" "5117.538,922.7" "0.15")
(command "_circle" "5117.163,922.7" "0.15")
(command "_circle" "5116.788,922.7" "0.075")
(command "_circle" "5116.413,922.7" "0.15")
(command "_circle" "5116.038,922.7" "0.075")
(command "_circle" "5115.663,922.7" "0.15")
(command "_circle" "5117.913,924.7" "0.075")
(command "_circle" "5117.538,924.7" "0.075")
(command "_circle" "5117.163,924.7" "0.075")
(command "_circle" "5116.788,924.7" "0.15")
(command "_circle" "5116.413,924.7" "0.15")
(command "_circle" "5116.038,924.7" "0.075")
(command "_circle" "5115.663,924.7" "0.15")
(command "_circle" "5117.913,926.7" "0.075")
(command "_circle" "5117.538,926.7" "0.15")
(command "_circle" "5117.163,926.7" "0.075")
(command "_circle" "5116.788,926.7" "0.15")
(command "_circle" "5116.413,926.7" "0.15")
(command "_circle" "5116.038,926.7" "0.075")
(command "_circle" "5115.663,926.7" "0.15")
(command "_circle" "5117.913,928.7" "0.075")
(command "_circle" "5117.538,928.7" "0.075")
(command "_circle" "5117.163,928.7" "0.15")
(command "_circle" "5116.788,928.7" "0.15")
(command "_circle" "5116.413,928.7" "0.15")
(command "_circle" "5116.038,928.7" "0.075")
(command "_circle" "5115.663,928.7" "0.15")
(command "_circle" "5117.913,930.7" "0.075")
(command "_circle" "5117.538,930.7" "0.15")
(command "_circle" "5117.163,930.7" "0.15")
(command "_circle" "5116.788,930.7" "0.15")
(command "_circle" "5116.413,930.7" "0.15")
(command "_circle" "5116.038,930.7" "0.075")
(command "_circle" "5115.663,930.7" "0.15")
(command "_circle" "5117.913,932.7" "0.075")
(command "_circle" "5117.538,932.7" "0.075")
(command "_circle" "5117.163,932.7" "0.075")
(command "_circle" "5116.788,932.7" "0.075")
(command "_circle" "5116.413,932.7" "0.075")
(command "_circle" "5116.038,932.7" "0.15")
(command "_circle" "5115.663,932.7" "0.15")
(command "_circle" "5117.913,934.7" "0.075")
(command "_circle" "5117.538,934.7" "0.15")
(command "_circle" "5117.163,934.7" "0.075")
(command "_circle" "5116.788,934.7" "0.075")
(command "_circle" "5116.413,934.7" "0.075")
(command "_circle" "5116.038,934.7" "0.15")
(command "_circle" "5115.663,934.7" "0.15")
(command "_circle" "5117.913,936.7" "0.075")
(command "_circle" "5117.538,936.7" "0.075")
(command "_circle" "5117.163,936.7" "0.15")
(command "_circle" "5116.788,936.7" "0.075")
(command "_circle" "5116.413,936.7" "0.075")
(command "_circle" "5116.038,936.7" "0.15")
(command "_circle" "5115.663,936.7" "0.15")
(command "_circle" "5117.913,938.7" "0.075")
(command "_circle" "5117.538,938.7" "0.15")
(command "_circle" "5117.163,938.7" "0.15")
(command "_circle" "5116.788,938.7" "0.075")
(command "_circle" "5116.413,938.7" "0.075")
(command "_circle" "5116.038,938.7" "0.15")
(command "_circle" "5115.663,938.7" "0.15")
(command "_circle" "5117.913,940.7" "0.075")
(command "_circle" "5117.538,940.7" "0.075")
(command "_circle" "5117.163,940.7" "0.075")
(command "_circle" "5116.788,940.7" "0.15")
(command "_circle" "5116.413,940.7" "0.075")
(command "_circle" "5116.038,940.7" "0.15")
(command "_circle" "5115.663,940.7" "0.15")
(command "_circle" "5117.913,942.7" "0.075")
(command "_circle" "5117.538,942.7" "0.15")
(command "_circle" "5117.163,942.7" "0.075")
(command "_circle" "5116.788,942.7" "0.15")
(command "_circle" "5116.413,942.7" "0.075")
(command "_circle" "5116.038,942.7" "0.15")
(command "_circle" "5115.663,942.7" "0.15")
(command "_circle" "5117.913,944.7" "0.075")
(command "_circle" "5117.538,944.7" "0.075")
(command "_circle" "5117.163,944.7" "0.15")
(command "_circle" "5116.788,944.7" "0.15")
(command "_circle" "5116.413,944.7" "0.075")
(command "_circle" "5116.038,944.7" "0.15")
(command "_circle" "5115.663,944.7" "0.15")
(command "_circle" "5117.913,946.7" "0.075")
(command "_circle" "5117.538,946.7" "0.15")
(command "_circle" "5117.163,946.7" "0.15")
(command "_circle" "5116.788,946.7" "0.15")
(command "_circle" "5116.413,946.7" "0.075")
(command "_circle" "5116.038,946.7" "0.15")
(command "_circle" "5115.663,946.7" "0.15")
(command "_circle" "5117.913,948.7" "0.075")
(command "_circle" "5117.538,948.7" "0.075")
(command "_circle" "5117.163,948.7" "0.075")
(command "_circle" "5116.788,948.7" "0.075")
(command "_circle" "5116.413,948.7" "0.15")
(command "_circle" "5116.038,948.7" "0.15")
(command "_circle" "5115.663,948.7" "0.15")
(command "_circle" "5117.913,950.7" "0.075")
(command "_circle" "5117.538,950.7" "0.15")
(command "_circle" "5117.163,950.7" "0.075")
(command "_circle" "5116.788,950.7" "0.075")
(command "_circle" "5116.413,950.7" "0.15")
(command "_circle" "5116.038,950.7" "0.15")
(command "_circle" "5115.663,950.7" "0.15")
(command "_circle" "5117.913,952.7" "0.075")
(command "_circle" "5117.538,952.7" "0.075")
(command "_circle" "5117.163,952.7" "0.15")
(command "_circle" "5116.788,952.7" "0.075")
(command "_circle" "5116.413,952.7" "0.15")
(command "_circle" "5116.038,952.7" "0.15")
(command "_circle" "5115.663,952.7" "0.15")
(command "_circle" "5117.913,954.7" "0.075")
(command "_circle" "5117.538,954.7" "0.15")
(command "_circle" "5117.163,954.7" "0.15")
(command "_circle" "5116.788,954.7" "0.075")
(command "_circle" "5116.413,954.7" "0.15")
(command "_circle" "5116.038,954.7" "0.15")
(command "_circle" "5115.663,954.7" "0.15")
(command "_circle" "5117.913,956.7" "0.075")
(command "_circle" "5117.538,956.7" "0.075")
(command "_circle" "5117.163,956.7" "0.075")
(command "_circle" "5116.788,956.7" "0.15")
(command "_circle" "5116.413,956.7" "0.15")
(command "_circle" "5116.038,956.7" "0.15")
(command "_circle" "5115.663,956.7" "0.15")
(command "_circle" "5117.913,958.7" "0.075")
(command "_circle" "5117.538,958.7" "0.15")
(command "_circle" "5117.163,958.7" "0.075")
(command "_circle" "5116.788,958.7" "0.15")
(command "_circle" "5116.413,958.7" "0.15")
(command "_circle" "5116.038,958.7" "0.15")
(command "_circle" "5115.663,958.7" "0.15")
(command "_circle" "5117.913,960.7" "0.075")
(command "_circle" "5117.538,960.7" "0.075")
(command "_circle" "5117.163,960.7" "0.15")
(command "_circle" "5116.788,960.7" "0.15")
(command "_circle" "5116.413,960.7" "0.15")
(command "_circle" "5116.038,960.7" "0.15")
(command "_circle" "5115.663,960.7" "0.15")
(command "_circle" "5117.913,962.7" "0.075")
(command "_circle" "5117.538,962.7" "0.15")
(command "_circle" "5117.163,962.7" "0.15")
(command "_circle" "5116.788,962.7" "0.15")
(command "_circle" "5116.413,962.7" "0.15")
(command "_circle" "5116.038,962.7" "0.15")
(command "_circle" "5115.663,962.7" "0.15")
(command "_layer" "set" "nitride" "")
(command "_layer" "set" "text" "")
(command-s "_text" "5106.863,963.3" "2" "-90" "a = 370 nm" )
(sssetfirst nil (ssget "_L"))
(if (not (numberp (vl-string-search "Mac" (getvar "platform")))) (c:txtexp))
(command "_layer" "set" "nitride" "")
(command "_layer" "set" "text" "")
(command-s "_text" "5103.863,963.3" "2" "-90" "gap = 270 nm" )
(sssetfirst nil (ssget "_L"))
(if (not (numberp (vl-string-search "Mac" (getvar "platform")))) (c:txtexp))
(command "_layer" "set" "nitride" "")
(command "_layer" "set" "text" "")
(command-s "_text" "5100.863,963.3" "2" "-90" "amplitude = 135.5 nm" )
(sssetfirst nil (ssget "_L"))
(if (not (numberp (vl-string-search "Mac" (getvar "platform")))) (c:txtexp))
(command "_layer" "set" "nitride" "")
(command "_layer" "set" "text" "")
(command-s "_text" "5097.863,963.3" "2" "-90" "start width = 280 nm" )
(sssetfirst nil (ssget "_L"))
(if (not (numberp (vl-string-search "Mac" (getvar "platform")))) (c:txtexp))
(command "_layer" "set" "nitride" "")
(command "_layer" "set" "text" "")
(command-s "_text" "5094.863,963.3" "2" "-90" "width = 298 nm" )
(sssetfirst nil (ssget "_L"))
(if (not (numberp (vl-string-search "Mac" (getvar "platform")))) (c:txtexp))
(command "_layer" "set" "nitride" "")
(command "_layer" "set" "text" "")
(command-s "_text" "5091.863,963.3" "2" "-90" "taper: 15" )
(sssetfirst nil (ssget "_L"))
(if (not (numberp (vl-string-search "Mac" (getvar "platform")))) (c:txtexp))
(command "_layer" "set" "nitride" "")
(command "_layer" "set" "text" "")
(command-s "_text" "5088.863,963.3" "2" "-90" "nominal: 150" )
(sssetfirst nil (ssget "_L"))
(if (not (numberp (vl-string-search "Mac" (getvar "platform")))) (c:txtexp))
(command "_layer" "set" "nitride" "")
(command "_layer" "set" "indicators" "")
(setq coords (list 
(list 5040.415 940) 
(list 5040.415 920) 
(list 5020.415 900) 
(list 5040.415 880) 
(list 5040.415 860) 
(list 5040.415 900) 
(list 5040.415 887.0711) 
(list 5027.4861 900) 
(list 5040.415 912.9289) 
(list 5040.415 900)))
(apply 'command (append '("pline") coords '("c")))
(command "._fillet" "radius" "1" "._fillet" "P" (entlast))
(setq coords (list 
(list 5199.585 940) 
(list 5199.585 920) 
(list 5219.585 900) 
(list 5199.585 880) 
(list 5199.585 860) 
(list 5199.585 900) 
(list 5199.585 887.0711) 
(list 5212.5139 900) 
(list 5199.585 912.9289) 
(list 5199.585 900)))
(apply 'command (append '("pline") coords '("c")))
(command "._fillet" "radius" "1" "._fillet" "P" (entlast))
(command "_layer" "set" "holes" "")
(command "_circle" "5038.0629,914.1124" "0.5")
(command "_circle" "5035.7109,911.7603" "0.5")
(command "_circle" "5033.3588,909.4083" "0.5")
(command "_circle" "5031.0067,907.0562" "0.5")
(command "_circle" "5028.6547,904.7041" "0.5")
(command "_circle" "5026.3026,902.3521" "0.5")
(command "_circle" "5023.9505,900" "0.5")
(command "_circle" "5026.3026,897.6479" "0.5")
(command "_circle" "5028.6547,895.2959" "0.5")
(command "_circle" "5031.0067,892.9438" "0.5")
(command "_circle" "5033.3588,890.5917" "0.5")
(command "_circle" "5035.7109,888.2397" "0.5")
(command "_circle" "5038.0629,885.8876" "0.5")
(command "_circle" "5201.9371,914.1124" "0.5")
(command "_circle" "5204.2891,911.7603" "0.5")
(command "_circle" "5206.6412,909.4083" "0.5")
(command "_circle" "5208.9933,907.0562" "0.5")
(command "_circle" "5211.3453,904.7041" "0.5")
(command "_circle" "5213.6974,902.3521" "0.5")
(command "_circle" "5216.0495,900" "0.5")
(command "_circle" "5213.6974,897.6479" "0.5")
(command "_circle" "5211.3453,895.2959" "0.5")
(command "_circle" "5208.9933,892.9438" "0.5")
(command "_circle" "5206.6412,890.5917" "0.5")
(command "_circle" "5204.2891,888.2397" "0.5")
(command "_circle" "5201.9371,885.8876" "0.5")
(command "_layer" "set" "nitride" "")
(command "_block" "blkcoupler16" "5120,900" coupler16 "")
(command "_insert" "blkcoupler16" "5120,900" "1" "1" "0")
(command "_insert" "blkcoupler16" "5120,900" "1" "1" "180")
(command "_block" "blksinglenanobeam16" "5120,900" singlenanobeam16 "")
(command "_insert" "blksinglenanobeam16" "5120,900" "1" "1" "0")
(command "_insert" "blksinglenanobeam16" "5120,900" "1" "1" "180")
(command "_block" "blkanglednodearray16" "5120,900" anglednodearray16 "")
(command "_insert" "blkanglednodearray16" "5120,900" "1" "1" "0")
(command "_insert" "blkanglednodearray16" "5120,900" "1" "1" "180")
(command "_block" "blkcooledsinglenanobeam16" "5120,900" cooledsinglenanobeam16 "")
(command "_insert" "blkcooledsinglenanobeam16" "5120,900" "1" "1" "0")
(command "_insert" "blkcooledsinglenanobeam16" "5120,900" "1" "1" "180")
(command "_block" "blkyjunction16" "5120,900" yjunction16 "")
(command "_insert" "blkyjunction16" "5120,900" "1" "1" "0")
(command "_insert" "blkyjunction16" "5120,900" "1" "1" "180")
; DRAWING BULGING VEE GROOVE
(command "_layer" "set" "vgroove" "")
(setq coords (list 
(list 5045.415 -605) 
(list 5045.415 0) 
(list 5045.415 0) 
(list 5045.415 1800) 
(list 5045.415 1800) 
(list 5045.415 2405) 
(list 5194.585 2405) 
(list 5194.585 1800) 
(list 5194.585 1800) 
(list 5194.585 0) 
(list 5194.585 0) 
(list 5194.585 -605)))
(apply 'command (append '("pline") coords '("c")))
(command "._fillet" "radius" "0" "._fillet" "P" (entlast))
(command "_layer" "set" "window" "")
(command "_rectangle" "5045.415,-1935" "5194.585,-600")
(command "_rectangle" "5045.415,2400" "5194.585,5300")
(command "_layer" "set" "grid" "")
(command "_rectangle" "5046.415,-1934" "5069.9433,-1909.2133")
(command "_array" "last" "" "R" "75" "3" "25.7867" "24.5283")
(command "_rectangle" "5121,-1934" "5144.5283,-1909.2133")
(command "_array" "last" "" "R" "75" "3" "25.7867" "24.5283")
(command "_rectangle" "5046.415,1" "5069.9433,25.7")
(command "_array" "last" "" "R" "70" "3" "25.7" "24.5283")
(command "_rectangle" "5121,1" "5144.5283,25.7")
(command "_array" "last" "" "R" "70" "3" "25.7" "24.5283")
(command "_rectangle" "5046.415,1801" "5069.9433,1825.9185")
(command "_array" "last" "" "R" "135" "3" "25.9185" "24.5283")
(command "_rectangle" "5121,1801" "5144.5283,1825.9185")
(command "_array" "last" "" "R" "135" "3" "25.9185" "24.5283")
(command "_layer" "set" "vgrooveFDA" "")
(command "_rectangle" "5194.585,-2233" "5045.415,-1933")
(command "_layer" "set" "nitride" "")
(command "_layer" "set" "holes" "")
(command "_circle" "5197.085,331.5" "0.5")
(command "_array" "last" "" "R" "379" "1" "3" "2.5")
(command "_circle" "5042.915,331.5" "0.5")
(command "_array" "last" "" "R" "379" "1" "3" "-2.5")
(command "_layer" "set" "nitride" "")
(command "_layer" "set" "window" "")
(command "_layer" "set" "window" "")
(command "_rectangle" "5199.585,0" "6426.225,1800")
(command "._fillet" "radius" "20" "._fillet" "P" (entlast))
(command "_layer" "set" "grid" "")
(command "_rectangle" "5200.585,1" "5225.1192,25.7")
(command "_array" "last" "" "R" "70" "48" "25.7" "25.5342")
; DRAWING REGION LAYER
(command "_layer" "set" "regionLayer16" "")
(command "_rectangle" "5040,-460" "5200,2260")
(command "_layer" "set" "nitride" "")
(setq coupler16 nil)
(setq singlenanobeam16 nil)
(setq anglednodearray16 nil)
(setq cooledsinglenanobeam16 nil)
(setq yjunction16 nil)
(command "_layer" "set" "extent" "")
(command "_rectangle" "-2040,-2480" "-2020,-2460")
(command "_rectangle" "7940,-2480" "7960,-2460")
(command "_rectangle" "-2040,8500" "-2020,8520")
(command "_rectangle" "7940,8500" "7960,8520")
(command "_layer" "set" "marks" "")
(setq coords (list 
(list 0 -880) 
(list 90 -880) 
(list 90 -810) 
(list 70 -810) 
(list 70 -790) 
(list 90 -790) 
(list 90 -880) 
(list 160 -880) 
(list 160 -720) 
(list 0 -720)))
(apply 'command (append '("pline") coords '("c")))
(setq coords (list 
(list 5760 -880) 
(list 5850 -880) 
(list 5850 -810) 
(list 5830 -810) 
(list 5830 -790) 
(list 5850 -790) 
(list 5850 -880) 
(list 5920 -880) 
(list 5920 -720) 
(list 5760 -720)))
(apply 'command (append '("pline") coords '("c")))
(setq coords (list 
(list 0 2640) 
(list 90 2640) 
(list 90 2710) 
(list 70 2710) 
(list 70 2730) 
(list 90 2730) 
(list 90 2640) 
(list 160 2640) 
(list 160 2800) 
(list 0 2800)))
(apply 'command (append '("pline") coords '("c")))
(setq coords (list 
(list 5760 2640) 
(list 5850 2640) 
(list 5850 2710) 
(list 5830 2710) 
(list 5830 2730) 
(list 5850 2730) 
(list 5850 2640) 
(list 5920 2640) 
(list 5920 2800) 
(list 5760 2800)))
(apply 'command (append '("pline") coords '("c")))
(command "_layer" "set" "marks" "")
(command "_rectangle" "70,-330" "90,-310")
(command "_rectangle" "5830,-330" "5850,-310")
(command "_rectangle" "70,2230" "90,2250")
(command "_rectangle" "5830,2230" "5850,2250")
(command "_layer" "set" "nitride" "")
(command "_zoom" "extents")
; DRAW LAYERS, SET COLORS
(command "_layer" "OFF" "grid" "")
(command "_saveas" "DXF" "Version" "2000" "" "/Users/Andrew/Documents/Repositories/fabrication/Writes/2016/09-September/2016-09-12/harald16.dxf")
