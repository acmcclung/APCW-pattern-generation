(defun x-coords (input-coords) (mapcar '(lambda (x) (nth 0 x)) input-coords))
(defun y-coords (input-coords) (mapcar '(lambda (x) (nth 1 x)) input-coords))
(defun remove-nil (in) (apply 'append (mapcar '(lambda (x) (if (not (null x)) (list x) ) ) in) ))
(defun get-coords (input-entity) (remove-nil (mapcar '(lambda (x) (if (= (car x) 10) (cdr x))) input-entity)))
(defun c:zoom-named (entname) (command "_zoom" "object" entname "")(princ))
(if (not (numberp (vl-string-search "Mac" (getvar "platform")))) (load "TXTEXP.LSP"))
;; NUMBER OF LAYERS: 16
; ERASE ALL
(command "_erase" "all" "")
; DRAW LAYERS, SET COLORS
(command "_layer" "new" "negYjunc" "")
(command "_layer" "new" "nitride" "")
(command "_layer" "new" "slices" "")
(command "_layer" "new" "holes" "")
(command "_layer" "new" "vgroove" "")
(command "_layer" "new" "vgrooveFDA" "")
(command "_layer" "new" "window" "")
(command "_layer" "new" "marks" "")
(command "_layer" "new" "extent" "")
(command "_layer" "new" "cover" "")
(command "_layer" "new" "grid" "")
(command "_layer" "new" "pads" "")
(command "_layer" "new" "text" "")
(command "_layer" "new" "fda1" "")
(command "_layer" "new" "prebias" "")
(command "_layer" "new" "phc" "")
(command "_layer" "new" "phccover" "")
(command "_layer" "new" "tethers" "")
(command "_layer" "new" "indicators" "")
(command "_layer" "new" "regionLayer1" "")
(command "_layer" "new" "regionLayer2" "")
(command "_layer" "new" "regionLayer3" "")
(command "_layer" "new" "regionLayer4" "")
(command "_layer" "new" "regionLayer5" "")
(command "_layer" "new" "regionLayer6" "")
(command "_layer" "new" "regionLayer7" "")
(command "_layer" "new" "regionLayer8" "")
(command "_layer" "new" "regionLayer9" "")
(command "_layer" "new" "regionLayer10" "")
(command "_layer" "new" "regionLayer11" "")
(command "_layer" "new" "regionLayer12" "")
(command "_layer" "new" "regionLayer13" "")
(command "_layer" "new" "regionLayer14" "")
(command "_layer" "new" "regionLayer15" "")
(command "_layer" "new" "regionLayer16" "")
(command "_layer" "color" "green" "negYjunc" "")
(command "_layer" "color" "white" "nitride" "")
(command "_layer" "color" "red" "slices" "")
(command "_layer" "color" "blue" "holes" "")
(command "_layer" "color" "green" "vgroove" "")
(command "_layer" "color" "red" "vgrooveFDA" "")
(command "_layer" "color" "yellow" "window" "")
(command "_layer" "color" "yellow" "marks" "")
(command "_layer" "color" "yellow" "extent" "")
(command "_layer" "color" "yellow" "cover" "")
(command "_layer" "color" "176" "grid" "")
(command "_layer" "color" "red" "pads" "")
(command "_layer" "color" "white" "text" "")
(command "_layer" "color" "1" "fda1" "")
(command "_layer" "color" "6" "prebias" "")
(command "_layer" "color" "5" "phc" "")
(command "_layer" "set" "negYjunc" "")
(command "_zoom" (list -0.05 -0.05) (list 0.05 0.05))
(command "_purge" "B" "*" "N")
; DEVICE #1
(command "_layer" "set" "window" "")
(command "_circle" "232.915,-415" "5")
(command "_layer" "set" "nitride" "")
(setq currobj nil)
(setq currobj (ssadd))
; DRAWING COUPLER
(setq coords (list 
(list 320.0615 -415) 
(list 320.0615 -413) 
(list 393.585 -413) 
(list 393.585 -413) 
(list 393.9677 -413.0761) 
(list 394.2921 -413.2929) 
(list 394.5089 -413.6173) 
(list 394.585 -414) 
(list 394.585 -411.8) 
(list 394.585 -411.8) 
(list 394.5089 -412.1827) 
(list 394.2921 -412.5071) 
(list 393.9677 -412.7239) 
(list 393.585 -412.8) 
(list 320.0615 -412.8) 
(list 320.0615 -410.8) 
(list 319.9385 -410.8) 
(list 319.9385 -412.8) 
(list 246.415 -412.8) 
(list 246.0323 -412.7239) 
(list 245.7079 -412.5071) 
(list 245.4911 -412.1827) 
(list 245.415 -411.8) 
(list 245.415 -411.8) 
(list 245.415 -414) 
(list 245.4911 -413.6173) 
(list 245.7079 -413.2929) 
(list 246.0323 -413.0761) 
(list 246.415 -413) 
(list 246.415 -413) 
(list 319.9385 -413) 
(list 319.9385 -415)))
(apply 'command (append '("pline") coords '("c")))
(setq currobj (ssadd (entlast) currobj))
(command "._fillet" "radius" "0.3" "._fillet" "P" (entlast))
(command "_layer" "set" "holes" "")
(command "_circle" "320,-412.9" "0.113")
(setq currobj (ssadd (entlast) currobj))
(command "_layer" "set" "nitride" "")
(command "_layer" "set" "text" "")
(command "_circle" "319.2,-415" "0.075")
(command "_circle" "319.2,-414.7" "0.075")
(command "_circle" "319.2,-414.4" "0.075")
(command "_circle" "318.9,-415" "0.075")
(command "_circle" "318.9,-414.7" "0.075")
(command "_circle" "318.9,-414.4" "0.075")
(command "_circle" "318.6,-415" "0.075")
(command "_circle" "318.6,-414.7" "0.075")
(command "_circle" "318.6,-414.4" "0.075")
(command "_layer" "set" "nitride" "")
(command "_layer" "set" "prebias" "")
(command "_rectangle" "245.415,-414" "394.585,-411.8")
(setq currobj (ssadd (entlast) currobj))
(command "_rectangle" "319.9385,-415" "320.0615,-410.8")
(setq currobj (ssadd (entlast) currobj))
(command "_layer" "set" "nitride" "")
(setq coupler1 currobj)
(setq currobj nil)
(setq currobj (ssadd))
; DRAWING SINGLE NANOBEAM
(setq coords (list 
(list 320.0615 -410.8) 
(list 320.0615 -409.1417) 
(list 320.0615 -407.4833) 
(list 320.0615 -405.825) 
(list 320.0615 -404.1667) 
(list 320.0615 -402.5083) 
(list 320.0615 -400.85) 
(list 320.0615 -399.1917) 
(list 320.0615 -397.5333) 
(list 320.0616 -395.875) 
(list 320.0616 -394.2167) 
(list 320.0616 -392.5583) 
(list 320.0616 -390.9) 
(list 320.0617 -389.2417) 
(list 320.0617 -387.5833) 
(list 320.0617 -385.925) 
(list 320.0618 -384.2667) 
(list 320.0619 -382.6083) 
(list 320.0619 -380.95) 
(list 320.062 -379.2917) 
(list 320.0621 -377.6333) 
(list 320.0622 -375.975) 
(list 320.0623 -374.3167) 
(list 320.0624 -372.6583) 
(list 320.0625 -371) 
(list 320.0626 -369.3417) 
(list 320.0628 -367.6833) 
(list 320.0629 -366.025) 
(list 320.0631 -364.3667) 
(list 320.0632 -362.7083) 
(list 320.0634 -361.05) 
(list 320.0636 -359.3917) 
(list 320.0638 -357.7333) 
(list 320.0641 -356.075) 
(list 320.0643 -354.4167) 
(list 320.0646 -352.7583) 
(list 320.0648 -351.1) 
(list 320.0651 -349.4417) 
(list 320.0654 -347.7833) 
(list 320.0657 -346.125) 
(list 320.0661 -344.4667) 
(list 320.0664 -342.8083) 
(list 320.0668 -341.15) 
(list 320.0672 -339.4917) 
(list 320.0676 -337.8333) 
(list 320.068 -336.175) 
(list 320.0685 -334.5167) 
(list 320.0689 -332.8583) 
(list 320.0694 -331.2) 
(list 320.0699 -329.5417) 
(list 320.0704 -327.8833) 
(list 320.071 -326.225) 
(list 320.0715 -324.5667) 
(list 320.0721 -322.9083) 
(list 320.0728 -321.25) 
(list 320.0734 -319.5917) 
(list 320.0741 -317.9333) 
(list 320.0747 -316.275) 
(list 320.0754 -314.6167) 
(list 320.0762 -312.9583) 
(list 320.0769 -311.3) 
(list 320.0777 -309.6417) 
(list 320.0785 -307.9833) 
(list 320.0794 -306.325) 
(list 320.0802 -304.6667) 
(list 320.0811 -303.0083) 
(list 320.082 -301.35) 
(list 320.083 -299.6917) 
(list 320.084 -298.0333) 
(list 320.085 -296.375) 
(list 320.086 -294.7167) 
(list 320.0871 -293.0583) 
(list 320.0882 -291.4) 
(list 320.0893 -289.7417) 
(list 320.0905 -288.0833) 
(list 320.0917 -286.425) 
(list 320.0929 -284.7667) 
(list 320.0941 -283.1083) 
(list 320.0954 -281.45) 
(list 320.0967 -279.7917) 
(list 320.0981 -278.1333) 
(list 320.0995 -276.475) 
(list 320.1009 -274.8167) 
(list 320.1024 -273.1583) 
(list 320.1039 -271.5) 
(list 320.1054 -269.8417) 
(list 320.107 -268.1833) 
(list 320.1086 -266.525) 
(list 320.1102 -264.8667) 
(list 320.1119 -263.2083) 
(list 320.1136 -261.55) 
(list 320.1154 -259.8917) 
(list 320.1172 -258.2333) 
(list 320.119 -256.575) 
(list 320.1209 -254.9167) 
(list 320.1228 -253.2583) 
(list 320.1247 -251.6) 
(list 320.1267 -249.9417) 
(list 320.1288 -248.2833) 
(list 320.1308 -246.625) 
(list 320.133 -244.9667) 
(list 320.1351 -243.3083) 
(list 320.1373 -241.65) 
(list 320.1396 -239.9917) 
(list 320.1419 -238.3333) 
(list 320.1442 -236.675) 
(list 320.1466 -235.0167) 
(list 320.1491 -233.3583) 
(list 320.1515 -231.7) 
(list 320.1541 -230.0417) 
(list 320.1566 -228.3833) 
(list 320.1592 -226.725) 
(list 320.1619 -225.0667) 
(list 320.1646 -223.4083) 
(list 320.1674 -221.75) 
(list 320.1702 -220.0917) 
(list 320.1731 -218.4333) 
(list 320.176 -216.775) 
(list 320.1789 -215.1167) 
(list 320.1819 -213.4583) 
(list 320.185 -211.8) 
(list 319.815 -211.8) 
(list 319.8181 -213.4583) 
(list 319.8211 -215.1167) 
(list 319.824 -216.775) 
(list 319.8269 -218.4333) 
(list 319.8298 -220.0917) 
(list 319.8326 -221.75) 
(list 319.8354 -223.4083) 
(list 319.8381 -225.0667) 
(list 319.8408 -226.725) 
(list 319.8434 -228.3833) 
(list 319.8459 -230.0417) 
(list 319.8485 -231.7) 
(list 319.8509 -233.3583) 
(list 319.8534 -235.0167) 
(list 319.8558 -236.675) 
(list 319.8581 -238.3333) 
(list 319.8604 -239.9917) 
(list 319.8627 -241.65) 
(list 319.8649 -243.3083) 
(list 319.867 -244.9667) 
(list 319.8692 -246.625) 
(list 319.8712 -248.2833) 
(list 319.8733 -249.9417) 
(list 319.8753 -251.6) 
(list 319.8772 -253.2583) 
(list 319.8791 -254.9167) 
(list 319.881 -256.575) 
(list 319.8828 -258.2333) 
(list 319.8846 -259.8917) 
(list 319.8864 -261.55) 
(list 319.8881 -263.2083) 
(list 319.8898 -264.8667) 
(list 319.8914 -266.525) 
(list 319.893 -268.1833) 
(list 319.8946 -269.8417) 
(list 319.8961 -271.5) 
(list 319.8976 -273.1583) 
(list 319.8991 -274.8167) 
(list 319.9005 -276.475) 
(list 319.9019 -278.1333) 
(list 319.9033 -279.7917) 
(list 319.9046 -281.45) 
(list 319.9059 -283.1083) 
(list 319.9071 -284.7667) 
(list 319.9083 -286.425) 
(list 319.9095 -288.0833) 
(list 319.9107 -289.7417) 
(list 319.9118 -291.4) 
(list 319.9129 -293.0583) 
(list 319.914 -294.7167) 
(list 319.915 -296.375) 
(list 319.916 -298.0333) 
(list 319.917 -299.6917) 
(list 319.918 -301.35) 
(list 319.9189 -303.0083) 
(list 319.9198 -304.6667) 
(list 319.9206 -306.325) 
(list 319.9215 -307.9833) 
(list 319.9223 -309.6417) 
(list 319.9231 -311.3) 
(list 319.9238 -312.9583) 
(list 319.9246 -314.6167) 
(list 319.9253 -316.275) 
(list 319.9259 -317.9333) 
(list 319.9266 -319.5917) 
(list 319.9272 -321.25) 
(list 319.9279 -322.9083) 
(list 319.9285 -324.5667) 
(list 319.929 -326.225) 
(list 319.9296 -327.8833) 
(list 319.9301 -329.5417) 
(list 319.9306 -331.2) 
(list 319.9311 -332.8583) 
(list 319.9315 -334.5167) 
(list 319.932 -336.175) 
(list 319.9324 -337.8333) 
(list 319.9328 -339.4917) 
(list 319.9332 -341.15) 
(list 319.9336 -342.8083) 
(list 319.9339 -344.4667) 
(list 319.9343 -346.125) 
(list 319.9346 -347.7833) 
(list 319.9349 -349.4417) 
(list 319.9352 -351.1) 
(list 319.9354 -352.7583) 
(list 319.9357 -354.4167) 
(list 319.9359 -356.075) 
(list 319.9362 -357.7333) 
(list 319.9364 -359.3917) 
(list 319.9366 -361.05) 
(list 319.9368 -362.7083) 
(list 319.9369 -364.3667) 
(list 319.9371 -366.025) 
(list 319.9372 -367.6833) 
(list 319.9374 -369.3417) 
(list 319.9375 -371) 
(list 319.9376 -372.6583) 
(list 319.9377 -374.3167) 
(list 319.9378 -375.975) 
(list 319.9379 -377.6333) 
(list 319.938 -379.2917) 
(list 319.9381 -380.95) 
(list 319.9381 -382.6083) 
(list 319.9382 -384.2667) 
(list 319.9383 -385.925) 
(list 319.9383 -387.5833) 
(list 319.9383 -389.2417) 
(list 319.9384 -390.9) 
(list 319.9384 -392.5583) 
(list 319.9384 -394.2167) 
(list 319.9384 -395.875) 
(list 319.9385 -397.5333) 
(list 319.9385 -399.1917) 
(list 319.9385 -400.85) 
(list 319.9385 -402.5083) 
(list 319.9385 -404.1667) 
(list 319.9385 -405.825) 
(list 319.9385 -407.4833) 
(list 319.9385 -409.1417) 
(list 319.9385 -410.8)))
(apply 'command (append '("pline") coords '("c")))
(setq currobj (ssadd (entlast) currobj))
(command "_layer" "set" "prebias" "")
(command "_rectangle" "319.815,-410.8" "320.185,-211.8")
(setq currobj (ssadd (entlast) currobj))
(command "_layer" "set" "nitride" "")
(setq singlenanobeam1 currobj)
(setq currobj nil)
(setq currobj (ssadd))
; DRAWING NODE ARRAY
(setq coords (list 
(list 320.185 -211.8) 
(list 320.5625 -201.8) 
(list 320.5625 -201.8) 
(list 320.5625 -200.8) 
(list 394.585 -212.6864) 
(list 394.585 -207.7434) 
(list 320.5625 -197.357) 
(list 320.5625 -196.357) 
(list 320.5625 -196.357) 
(list 320.2625 -186.357) 
(list 319.7375 -186.357) 
(list 319.4375 -196.357) 
(list 319.4375 -196.357) 
(list 319.4375 -197.357) 
(list 245.415 -207.7434) 
(list 245.415 -212.6864) 
(list 319.4375 -200.8) 
(list 319.4375 -201.8) 
(list 319.4375 -201.8) 
(list 319.815 -211.8)))
(apply 'command (append '("pline") coords '("c")))
(setq currobj (ssadd (entlast) currobj))
(command "_layer" "set" "prebias" "")
(setq coords (list 
(list 319.4375 -212.6864) 
(list 319.4375 -200.8) 
(list 245.415 -212.6864) 
(list 245.415 -207.7434) 
(list 319.4375 -197.357) 
(list 319.4375 -186.357) 
(list 320.5625 -186.357) 
(list 320.5625 -197.357) 
(list 394.585 -207.7434) 
(list 394.585 -212.6864) 
(list 320.5625 -200.8) 
(list 320.5625 -212.6864)))
(apply 'command (append '("pline") coords '("c")))
(setq currobj (ssadd (entlast) currobj))
(command "_layer" "set" "nitride" "")
(command "_layer" "set" "fda1" "")
(setq coords (list 
(list 320.5625 -200.657) 
(list 394.585 -212.5434) 
(list 394.585 -212.3664) 
(list 320.5625 -200.58)))
(apply 'command (append '("pline") coords '("c")))
(setq currobj (ssadd (entlast) currobj))
(setq coords (list 
(list 320.5625 -200.437) 
(list 394.585 -212.2234) 
(list 394.585 -212.0464) 
(list 320.5625 -200.36)))
(apply 'command (append '("pline") coords '("c")))
(setq currobj (ssadd (entlast) currobj))
(setq coords (list 
(list 320.5625 -200.217) 
(list 394.585 -211.9034) 
(list 394.585 -211.7264) 
(list 320.5625 -200.14)))
(apply 'command (append '("pline") coords '("c")))
(setq currobj (ssadd (entlast) currobj))
(setq coords (list 
(list 320.5625 -199.997) 
(list 394.585 -211.5834) 
(list 394.585 -211.4064) 
(list 320.5625 -199.92)))
(apply 'command (append '("pline") coords '("c")))
(setq currobj (ssadd (entlast) currobj))
(setq coords (list 
(list 320.5625 -199.777) 
(list 394.585 -211.2634) 
(list 394.585 -211.0864) 
(list 320.5625 -199.7)))
(apply 'command (append '("pline") coords '("c")))
(setq currobj (ssadd (entlast) currobj))
(setq coords (list 
(list 320.5625 -199.557) 
(list 394.585 -210.9434) 
(list 394.585 -210.7664) 
(list 320.5625 -199.48)))
(apply 'command (append '("pline") coords '("c")))
(setq currobj (ssadd (entlast) currobj))
(setq coords (list 
(list 320.5625 -199.337) 
(list 394.585 -210.6234) 
(list 394.585 -210.4464) 
(list 320.5625 -199.26)))
(apply 'command (append '("pline") coords '("c")))
(setq currobj (ssadd (entlast) currobj))
(setq coords (list 
(list 320.5625 -199.117) 
(list 394.585 -210.3034) 
(list 394.585 -210.1264) 
(list 320.5625 -199.04)))
(apply 'command (append '("pline") coords '("c")))
(setq currobj (ssadd (entlast) currobj))
(setq coords (list 
(list 320.5625 -198.897) 
(list 394.585 -209.9834) 
(list 394.585 -209.8064) 
(list 320.5625 -198.82)))
(apply 'command (append '("pline") coords '("c")))
(setq currobj (ssadd (entlast) currobj))
(setq coords (list 
(list 320.5625 -198.677) 
(list 394.585 -209.6634) 
(list 394.585 -209.4864) 
(list 320.5625 -198.6)))
(apply 'command (append '("pline") coords '("c")))
(setq currobj (ssadd (entlast) currobj))
(setq coords (list 
(list 320.5625 -198.457) 
(list 394.585 -209.3434) 
(list 394.585 -209.1664) 
(list 320.5625 -198.38)))
(apply 'command (append '("pline") coords '("c")))
(setq currobj (ssadd (entlast) currobj))
(setq coords (list 
(list 320.5625 -198.237) 
(list 394.585 -209.0234) 
(list 394.585 -208.8464) 
(list 320.5625 -198.16)))
(apply 'command (append '("pline") coords '("c")))
(setq currobj (ssadd (entlast) currobj))
(setq coords (list 
(list 320.5625 -198.017) 
(list 394.585 -208.7034) 
(list 394.585 -208.5264) 
(list 320.5625 -197.94)))
(apply 'command (append '("pline") coords '("c")))
(setq currobj (ssadd (entlast) currobj))
(setq coords (list 
(list 320.5625 -197.797) 
(list 394.585 -208.3834) 
(list 394.585 -208.2064) 
(list 320.5625 -197.72)))
(apply 'command (append '("pline") coords '("c")))
(setq currobj (ssadd (entlast) currobj))
(setq coords (list 
(list 320.5625 -197.577) 
(list 394.585 -208.0634) 
(list 394.585 -207.8864) 
(list 320.5625 -197.5)))
(apply 'command (append '("pline") coords '("c")))
(setq currobj (ssadd (entlast) currobj))
(setq coords (list 
(list 319.4375 -197.5) 
(list 245.415 -207.8864) 
(list 245.415 -208.0634) 
(list 319.4375 -197.577)))
(apply 'command (append '("pline") coords '("c")))
(setq currobj (ssadd (entlast) currobj))
(setq coords (list 
(list 319.4375 -197.72) 
(list 245.415 -208.2064) 
(list 245.415 -208.3834) 
(list 319.4375 -197.797)))
(apply 'command (append '("pline") coords '("c")))
(setq currobj (ssadd (entlast) currobj))
(setq coords (list 
(list 319.4375 -197.94) 
(list 245.415 -208.5264) 
(list 245.415 -208.7034) 
(list 319.4375 -198.017)))
(apply 'command (append '("pline") coords '("c")))
(setq currobj (ssadd (entlast) currobj))
(setq coords (list 
(list 319.4375 -198.16) 
(list 245.415 -208.8464) 
(list 245.415 -209.0234) 
(list 319.4375 -198.237)))
(apply 'command (append '("pline") coords '("c")))
(setq currobj (ssadd (entlast) currobj))
(setq coords (list 
(list 319.4375 -198.38) 
(list 245.415 -209.1664) 
(list 245.415 -209.3434) 
(list 319.4375 -198.457)))
(apply 'command (append '("pline") coords '("c")))
(setq currobj (ssadd (entlast) currobj))
(setq coords (list 
(list 319.4375 -198.6) 
(list 245.415 -209.4864) 
(list 245.415 -209.6634) 
(list 319.4375 -198.677)))
(apply 'command (append '("pline") coords '("c")))
(setq currobj (ssadd (entlast) currobj))
(setq coords (list 
(list 319.4375 -198.82) 
(list 245.415 -209.8064) 
(list 245.415 -209.9834) 
(list 319.4375 -198.897)))
(apply 'command (append '("pline") coords '("c")))
(setq currobj (ssadd (entlast) currobj))
(setq coords (list 
(list 319.4375 -199.04) 
(list 245.415 -210.1264) 
(list 245.415 -210.3034) 
(list 319.4375 -199.117)))
(apply 'command (append '("pline") coords '("c")))
(setq currobj (ssadd (entlast) currobj))
(setq coords (list 
(list 319.4375 -199.26) 
(list 245.415 -210.4464) 
(list 245.415 -210.6234) 
(list 319.4375 -199.337)))
(apply 'command (append '("pline") coords '("c")))
(setq currobj (ssadd (entlast) currobj))
(setq coords (list 
(list 319.4375 -199.48) 
(list 245.415 -210.7664) 
(list 245.415 -210.9434) 
(list 319.4375 -199.557)))
(apply 'command (append '("pline") coords '("c")))
(setq currobj (ssadd (entlast) currobj))
(setq coords (list 
(list 319.4375 -199.7) 
(list 245.415 -211.0864) 
(list 245.415 -211.2634) 
(list 319.4375 -199.777)))
(apply 'command (append '("pline") coords '("c")))
(setq currobj (ssadd (entlast) currobj))
(setq coords (list 
(list 319.4375 -199.92) 
(list 245.415 -211.4064) 
(list 245.415 -211.5834) 
(list 319.4375 -199.997)))
(apply 'command (append '("pline") coords '("c")))
(setq currobj (ssadd (entlast) currobj))
(setq coords (list 
(list 319.4375 -200.14) 
(list 245.415 -211.7264) 
(list 245.415 -211.9034) 
(list 319.4375 -200.217)))
(apply 'command (append '("pline") coords '("c")))
(setq currobj (ssadd (entlast) currobj))
(setq coords (list 
(list 319.4375 -200.36) 
(list 245.415 -212.0464) 
(list 245.415 -212.2234) 
(list 319.4375 -200.437)))
(apply 'command (append '("pline") coords '("c")))
(setq currobj (ssadd (entlast) currobj))
(setq coords (list 
(list 319.4375 -200.58) 
(list 245.415 -212.3664) 
(list 245.415 -212.5434) 
(list 319.4375 -200.657)))
(apply 'command (append '("pline") coords '("c")))
(setq currobj (ssadd (entlast) currobj))
(command "_layer" "set" "nitride" "")
(command "_layer" "set" "text" "")
(command "_circle" "318.985,-211.8" "0.075")
(command "_circle" "318.985,-211.5" "0.075")
(command "_circle" "318.985,-211.2" "0.075")
(command "_circle" "318.985,-210.9" "0.075")
(command "_circle" "318.985,-210.6" "0.075")
(command "_circle" "318.685,-211.8" "0.075")
(command "_circle" "318.685,-211.5" "0.075")
(command "_circle" "318.685,-211.2" "0.075")
(command "_circle" "318.685,-210.9" "0.075")
(command "_circle" "318.685,-210.6" "0.075")
(command "_circle" "318.385,-211.8" "0.075")
(command "_circle" "318.385,-211.5" "0.075")
(command "_circle" "318.385,-211.2" "0.075")
(command "_circle" "318.385,-210.9" "0.075")
(command "_circle" "318.385,-210.6" "0.075")
(command "_circle" "318.085,-211.8" "0.075")
(command "_circle" "318.085,-211.5" "0.075")
(command "_circle" "318.085,-211.2" "0.075")
(command "_circle" "318.085,-210.9" "0.075")
(command "_circle" "318.085,-210.6" "0.075")
(command "_circle" "317.785,-211.8" "0.075")
(command "_circle" "317.785,-211.5" "0.075")
(command "_circle" "317.785,-211.2" "0.075")
(command "_circle" "317.785,-210.9" "0.075")
(command "_circle" "317.785,-210.6" "0.075")
(command "_layer" "set" "nitride" "")
(setq anglednodearray1 currobj)
(setq currobj nil)
(setq currobj (ssadd))
; DRAWING COOLED SINGLE NANOBEAM
(setq coords (list 
(list 320.2625 -186.357) 
(list 320.2625 -181.357) 
(list 319.7375 -181.357) 
(list 319.7375 -186.357)))
(apply 'command (append '("pline") coords '("c")))
(setq currobj (ssadd (entlast) currobj))
(command "_layer" "set" "prebias" "")
(command "_rectangle" "319.7375,-186.357" "320.2625,-181.357")
(setq currobj (ssadd (entlast) currobj))
(command "_layer" "set" "nitride" "")
(setq coords (list 
(list 320.2625 -181.357) 
(list 320.5625 -171.357) 
(list 320.5625 -171.357) 
(list 320.5625 -170.357) 
(list 394.585 -171.107) 
(list 394.585 -166.164) 
(list 320.5625 -166.914) 
(list 320.5625 -165.914) 
(list 320.5625 -165.914) 
(list 320.2625 -155.914) 
(list 319.7375 -155.914) 
(list 319.4375 -165.914) 
(list 319.4375 -165.914) 
(list 319.4375 -166.914) 
(list 245.415 -166.164) 
(list 245.415 -171.107) 
(list 319.4375 -170.357) 
(list 319.4375 -171.357) 
(list 319.4375 -171.357) 
(list 319.7375 -181.357)))
(apply 'command (append '("pline") coords '("c")))
(setq currobj (ssadd (entlast) currobj))
(command "_layer" "set" "prebias" "")
(setq coords (list 
(list 319.4375 -181.357) 
(list 319.4375 -170.357) 
(list 245.415 -171.107) 
(list 245.415 -166.164) 
(list 319.4375 -166.914) 
(list 319.4375 -155.914) 
(list 320.5625 -155.914) 
(list 320.5625 -166.914) 
(list 394.585 -166.164) 
(list 394.585 -171.107) 
(list 320.5625 -170.357) 
(list 320.5625 -181.357)))
(apply 'command (append '("pline") coords '("c")))
(setq currobj (ssadd (entlast) currobj))
(command "_layer" "set" "nitride" "")
(command "_layer" "set" "fda1" "")
(setq coords (list 
(list 320.5625 -170.214) 
(list 394.585 -170.964) 
(list 394.585 -170.787) 
(list 320.5625 -170.137)))
(apply 'command (append '("pline") coords '("c")))
(setq currobj (ssadd (entlast) currobj))
(setq coords (list 
(list 320.5625 -169.994) 
(list 394.585 -170.644) 
(list 394.585 -170.467) 
(list 320.5625 -169.917)))
(apply 'command (append '("pline") coords '("c")))
(setq currobj (ssadd (entlast) currobj))
(setq coords (list 
(list 320.5625 -169.774) 
(list 394.585 -170.324) 
(list 394.585 -170.147) 
(list 320.5625 -169.697)))
(apply 'command (append '("pline") coords '("c")))
(setq currobj (ssadd (entlast) currobj))
(setq coords (list 
(list 320.5625 -169.554) 
(list 394.585 -170.004) 
(list 394.585 -169.827) 
(list 320.5625 -169.477)))
(apply 'command (append '("pline") coords '("c")))
(setq currobj (ssadd (entlast) currobj))
(setq coords (list 
(list 320.5625 -169.334) 
(list 394.585 -169.684) 
(list 394.585 -169.507) 
(list 320.5625 -169.257)))
(apply 'command (append '("pline") coords '("c")))
(setq currobj (ssadd (entlast) currobj))
(setq coords (list 
(list 320.5625 -169.114) 
(list 394.585 -169.364) 
(list 394.585 -169.187) 
(list 320.5625 -169.037)))
(apply 'command (append '("pline") coords '("c")))
(setq currobj (ssadd (entlast) currobj))
(setq coords (list 
(list 320.5625 -168.894) 
(list 394.585 -169.044) 
(list 394.585 -168.867) 
(list 320.5625 -168.817)))
(apply 'command (append '("pline") coords '("c")))
(setq currobj (ssadd (entlast) currobj))
(setq coords (list 
(list 320.5625 -168.674) 
(list 394.585 -168.724) 
(list 394.585 -168.547) 
(list 320.5625 -168.597)))
(apply 'command (append '("pline") coords '("c")))
(setq currobj (ssadd (entlast) currobj))
(setq coords (list 
(list 320.5625 -168.454) 
(list 394.585 -168.404) 
(list 394.585 -168.227) 
(list 320.5625 -168.377)))
(apply 'command (append '("pline") coords '("c")))
(setq currobj (ssadd (entlast) currobj))
(setq coords (list 
(list 320.5625 -168.234) 
(list 394.585 -168.084) 
(list 394.585 -167.907) 
(list 320.5625 -168.157)))
(apply 'command (append '("pline") coords '("c")))
(setq currobj (ssadd (entlast) currobj))
(setq coords (list 
(list 320.5625 -168.014) 
(list 394.585 -167.764) 
(list 394.585 -167.587) 
(list 320.5625 -167.937)))
(apply 'command (append '("pline") coords '("c")))
(setq currobj (ssadd (entlast) currobj))
(setq coords (list 
(list 320.5625 -167.794) 
(list 394.585 -167.444) 
(list 394.585 -167.267) 
(list 320.5625 -167.717)))
(apply 'command (append '("pline") coords '("c")))
(setq currobj (ssadd (entlast) currobj))
(setq coords (list 
(list 320.5625 -167.574) 
(list 394.585 -167.124) 
(list 394.585 -166.947) 
(list 320.5625 -167.497)))
(apply 'command (append '("pline") coords '("c")))
(setq currobj (ssadd (entlast) currobj))
(setq coords (list 
(list 320.5625 -167.354) 
(list 394.585 -166.804) 
(list 394.585 -166.627) 
(list 320.5625 -167.277)))
(apply 'command (append '("pline") coords '("c")))
(setq currobj (ssadd (entlast) currobj))
(setq coords (list 
(list 320.5625 -167.134) 
(list 394.585 -166.484) 
(list 394.585 -166.307) 
(list 320.5625 -167.057)))
(apply 'command (append '("pline") coords '("c")))
(setq currobj (ssadd (entlast) currobj))
(setq coords (list 
(list 319.4375 -167.057) 
(list 245.415 -166.307) 
(list 245.415 -166.484) 
(list 319.4375 -167.134)))
(apply 'command (append '("pline") coords '("c")))
(setq currobj (ssadd (entlast) currobj))
(setq coords (list 
(list 319.4375 -167.277) 
(list 245.415 -166.627) 
(list 245.415 -166.804) 
(list 319.4375 -167.354)))
(apply 'command (append '("pline") coords '("c")))
(setq currobj (ssadd (entlast) currobj))
(setq coords (list 
(list 319.4375 -167.497) 
(list 245.415 -166.947) 
(list 245.415 -167.124) 
(list 319.4375 -167.574)))
(apply 'command (append '("pline") coords '("c")))
(setq currobj (ssadd (entlast) currobj))
(setq coords (list 
(list 319.4375 -167.717) 
(list 245.415 -167.267) 
(list 245.415 -167.444) 
(list 319.4375 -167.794)))
(apply 'command (append '("pline") coords '("c")))
(setq currobj (ssadd (entlast) currobj))
(setq coords (list 
(list 319.4375 -167.937) 
(list 245.415 -167.587) 
(list 245.415 -167.764) 
(list 319.4375 -168.014)))
(apply 'command (append '("pline") coords '("c")))
(setq currobj (ssadd (entlast) currobj))
(setq coords (list 
(list 319.4375 -168.157) 
(list 245.415 -167.907) 
(list 245.415 -168.084) 
(list 319.4375 -168.234)))
(apply 'command (append '("pline") coords '("c")))
(setq currobj (ssadd (entlast) currobj))
(setq coords (list 
(list 319.4375 -168.377) 
(list 245.415 -168.227) 
(list 245.415 -168.404) 
(list 319.4375 -168.454)))
(apply 'command (append '("pline") coords '("c")))
(setq currobj (ssadd (entlast) currobj))
(setq coords (list 
(list 319.4375 -168.597) 
(list 245.415 -168.547) 
(list 245.415 -168.724) 
(list 319.4375 -168.674)))
(apply 'command (append '("pline") coords '("c")))
(setq currobj (ssadd (entlast) currobj))
(setq coords (list 
(list 319.4375 -168.817) 
(list 245.415 -168.867) 
(list 245.415 -169.044) 
(list 319.4375 -168.894)))
(apply 'command (append '("pline") coords '("c")))
(setq currobj (ssadd (entlast) currobj))
(setq coords (list 
(list 319.4375 -169.037) 
(list 245.415 -169.187) 
(list 245.415 -169.364) 
(list 319.4375 -169.114)))
(apply 'command (append '("pline") coords '("c")))
(setq currobj (ssadd (entlast) currobj))
(setq coords (list 
(list 319.4375 -169.257) 
(list 245.415 -169.507) 
(list 245.415 -169.684) 
(list 319.4375 -169.334)))
(apply 'command (append '("pline") coords '("c")))
(setq currobj (ssadd (entlast) currobj))
(setq coords (list 
(list 319.4375 -169.477) 
(list 245.415 -169.827) 
(list 245.415 -170.004) 
(list 319.4375 -169.554)))
(apply 'command (append '("pline") coords '("c")))
(setq currobj (ssadd (entlast) currobj))
(setq coords (list 
(list 319.4375 -169.697) 
(list 245.415 -170.147) 
(list 245.415 -170.324) 
(list 319.4375 -169.774)))
(apply 'command (append '("pline") coords '("c")))
(setq currobj (ssadd (entlast) currobj))
(setq coords (list 
(list 319.4375 -169.917) 
(list 245.415 -170.467) 
(list 245.415 -170.644) 
(list 319.4375 -169.994)))
(apply 'command (append '("pline") coords '("c")))
(setq currobj (ssadd (entlast) currobj))
(setq coords (list 
(list 319.4375 -170.137) 
(list 245.415 -170.787) 
(list 245.415 -170.964) 
(list 319.4375 -170.214)))
(apply 'command (append '("pline") coords '("c")))
(setq currobj (ssadd (entlast) currobj))
(command "_layer" "set" "nitride" "")
(command "_layer" "set" "text" "")
(command "_circle" "319.0625,-181.357" "0.075")
(command "_circle" "319.0625,-181.057" "0.075")
(command "_circle" "319.0625,-180.757" "0.075")
(command "_circle" "319.0625,-180.457" "0.075")
(command "_circle" "319.0625,-180.157" "0.075")
(command "_circle" "318.7625,-181.357" "0.075")
(command "_circle" "318.7625,-181.057" "0.075")
(command "_circle" "318.7625,-180.757" "0.075")
(command "_circle" "318.7625,-180.457" "0.075")
(command "_circle" "318.7625,-180.157" "0.075")
(command "_circle" "318.4625,-181.357" "0.075")
(command "_circle" "318.4625,-181.057" "0.075")
(command "_circle" "318.4625,-180.757" "0.075")
(command "_circle" "318.4625,-180.457" "0.075")
(command "_circle" "318.4625,-180.157" "0.075")
(command "_circle" "318.1625,-181.357" "0.075")
(command "_circle" "318.1625,-181.057" "0.075")
(command "_circle" "318.1625,-180.757" "0.075")
(command "_circle" "318.1625,-180.457" "0.075")
(command "_circle" "318.1625,-180.157" "0.075")
(command "_circle" "317.8625,-181.357" "0.075")
(command "_circle" "317.8625,-181.057" "0.075")
(command "_circle" "317.8625,-180.757" "0.075")
(command "_circle" "317.8625,-180.457" "0.075")
(command "_circle" "317.8625,-180.157" "0.075")
(command "_layer" "set" "nitride" "")
(setq coords (list 
(list 320.2625 -155.914) 
(list 320.2625 -40.2693) 
(list 319.7375 -40.2693) 
(list 319.7375 -155.914)))
(apply 'command (append '("pline") coords '("c")))
(setq currobj (ssadd (entlast) currobj))
(command "_layer" "set" "prebias" "")
(command "_rectangle" "319.7375,-155.914" "320.2625,-40.2693")
(setq currobj (ssadd (entlast) currobj))
(command "_layer" "set" "nitride" "")
(setq coords (list 
(list 320.2625 -40.2693) 
(list 320.5625 -30.2693) 
(list 320.5625 -30.2693) 
(list 320.5625 -29.2693) 
(list 394.585 -30.0193) 
(list 394.585 -25.0763) 
(list 320.5625 -25.8263) 
(list 320.5625 -24.8263) 
(list 320.5625 -24.8263) 
(list 320.2625 -14.8263) 
(list 319.7375 -14.8263) 
(list 319.4375 -24.8263) 
(list 319.4375 -24.8263) 
(list 319.4375 -25.8263) 
(list 245.415 -25.0763) 
(list 245.415 -30.0193) 
(list 319.4375 -29.2693) 
(list 319.4375 -30.2693) 
(list 319.4375 -30.2693) 
(list 319.7375 -40.2693)))
(apply 'command (append '("pline") coords '("c")))
(setq currobj (ssadd (entlast) currobj))
(command "_layer" "set" "prebias" "")
(setq coords (list 
(list 319.4375 -40.2693) 
(list 319.4375 -29.2693) 
(list 245.415 -30.0193) 
(list 245.415 -25.0763) 
(list 319.4375 -25.8263) 
(list 319.4375 -14.8263) 
(list 320.5625 -14.8263) 
(list 320.5625 -25.8263) 
(list 394.585 -25.0763) 
(list 394.585 -30.0193) 
(list 320.5625 -29.2693) 
(list 320.5625 -40.2693)))
(apply 'command (append '("pline") coords '("c")))
(setq currobj (ssadd (entlast) currobj))
(command "_layer" "set" "nitride" "")
(command "_layer" "set" "fda1" "")
(setq coords (list 
(list 320.5625 -29.1263) 
(list 394.585 -29.8763) 
(list 394.585 -29.6993) 
(list 320.5625 -29.0493)))
(apply 'command (append '("pline") coords '("c")))
(setq currobj (ssadd (entlast) currobj))
(setq coords (list 
(list 320.5625 -28.9063) 
(list 394.585 -29.5563) 
(list 394.585 -29.3793) 
(list 320.5625 -28.8293)))
(apply 'command (append '("pline") coords '("c")))
(setq currobj (ssadd (entlast) currobj))
(setq coords (list 
(list 320.5625 -28.6863) 
(list 394.585 -29.2363) 
(list 394.585 -29.0593) 
(list 320.5625 -28.6093)))
(apply 'command (append '("pline") coords '("c")))
(setq currobj (ssadd (entlast) currobj))
(setq coords (list 
(list 320.5625 -28.4663) 
(list 394.585 -28.9163) 
(list 394.585 -28.7393) 
(list 320.5625 -28.3893)))
(apply 'command (append '("pline") coords '("c")))
(setq currobj (ssadd (entlast) currobj))
(setq coords (list 
(list 320.5625 -28.2463) 
(list 394.585 -28.5963) 
(list 394.585 -28.4193) 
(list 320.5625 -28.1693)))
(apply 'command (append '("pline") coords '("c")))
(setq currobj (ssadd (entlast) currobj))
(setq coords (list 
(list 320.5625 -28.0263) 
(list 394.585 -28.2763) 
(list 394.585 -28.0993) 
(list 320.5625 -27.9493)))
(apply 'command (append '("pline") coords '("c")))
(setq currobj (ssadd (entlast) currobj))
(setq coords (list 
(list 320.5625 -27.8063) 
(list 394.585 -27.9563) 
(list 394.585 -27.7793) 
(list 320.5625 -27.7293)))
(apply 'command (append '("pline") coords '("c")))
(setq currobj (ssadd (entlast) currobj))
(setq coords (list 
(list 320.5625 -27.5863) 
(list 394.585 -27.6363) 
(list 394.585 -27.4593) 
(list 320.5625 -27.5093)))
(apply 'command (append '("pline") coords '("c")))
(setq currobj (ssadd (entlast) currobj))
(setq coords (list 
(list 320.5625 -27.3663) 
(list 394.585 -27.3163) 
(list 394.585 -27.1393) 
(list 320.5625 -27.2893)))
(apply 'command (append '("pline") coords '("c")))
(setq currobj (ssadd (entlast) currobj))
(setq coords (list 
(list 320.5625 -27.1463) 
(list 394.585 -26.9963) 
(list 394.585 -26.8193) 
(list 320.5625 -27.0693)))
(apply 'command (append '("pline") coords '("c")))
(setq currobj (ssadd (entlast) currobj))
(setq coords (list 
(list 320.5625 -26.9263) 
(list 394.585 -26.6763) 
(list 394.585 -26.4993) 
(list 320.5625 -26.8493)))
(apply 'command (append '("pline") coords '("c")))
(setq currobj (ssadd (entlast) currobj))
(setq coords (list 
(list 320.5625 -26.7063) 
(list 394.585 -26.3563) 
(list 394.585 -26.1793) 
(list 320.5625 -26.6293)))
(apply 'command (append '("pline") coords '("c")))
(setq currobj (ssadd (entlast) currobj))
(setq coords (list 
(list 320.5625 -26.4863) 
(list 394.585 -26.0363) 
(list 394.585 -25.8593) 
(list 320.5625 -26.4093)))
(apply 'command (append '("pline") coords '("c")))
(setq currobj (ssadd (entlast) currobj))
(setq coords (list 
(list 320.5625 -26.2663) 
(list 394.585 -25.7163) 
(list 394.585 -25.5393) 
(list 320.5625 -26.1893)))
(apply 'command (append '("pline") coords '("c")))
(setq currobj (ssadd (entlast) currobj))
(setq coords (list 
(list 320.5625 -26.0463) 
(list 394.585 -25.3963) 
(list 394.585 -25.2193) 
(list 320.5625 -25.9693)))
(apply 'command (append '("pline") coords '("c")))
(setq currobj (ssadd (entlast) currobj))
(setq coords (list 
(list 319.4375 -25.9693) 
(list 245.415 -25.2193) 
(list 245.415 -25.3963) 
(list 319.4375 -26.0463)))
(apply 'command (append '("pline") coords '("c")))
(setq currobj (ssadd (entlast) currobj))
(setq coords (list 
(list 319.4375 -26.1893) 
(list 245.415 -25.5393) 
(list 245.415 -25.7163) 
(list 319.4375 -26.2663)))
(apply 'command (append '("pline") coords '("c")))
(setq currobj (ssadd (entlast) currobj))
(setq coords (list 
(list 319.4375 -26.4093) 
(list 245.415 -25.8593) 
(list 245.415 -26.0363) 
(list 319.4375 -26.4863)))
(apply 'command (append '("pline") coords '("c")))
(setq currobj (ssadd (entlast) currobj))
(setq coords (list 
(list 319.4375 -26.6293) 
(list 245.415 -26.1793) 
(list 245.415 -26.3563) 
(list 319.4375 -26.7063)))
(apply 'command (append '("pline") coords '("c")))
(setq currobj (ssadd (entlast) currobj))
(setq coords (list 
(list 319.4375 -26.8493) 
(list 245.415 -26.4993) 
(list 245.415 -26.6763) 
(list 319.4375 -26.9263)))
(apply 'command (append '("pline") coords '("c")))
(setq currobj (ssadd (entlast) currobj))
(setq coords (list 
(list 319.4375 -27.0693) 
(list 245.415 -26.8193) 
(list 245.415 -26.9963) 
(list 319.4375 -27.1463)))
(apply 'command (append '("pline") coords '("c")))
(setq currobj (ssadd (entlast) currobj))
(setq coords (list 
(list 319.4375 -27.2893) 
(list 245.415 -27.1393) 
(list 245.415 -27.3163) 
(list 319.4375 -27.3663)))
(apply 'command (append '("pline") coords '("c")))
(setq currobj (ssadd (entlast) currobj))
(setq coords (list 
(list 319.4375 -27.5093) 
(list 245.415 -27.4593) 
(list 245.415 -27.6363) 
(list 319.4375 -27.5863)))
(apply 'command (append '("pline") coords '("c")))
(setq currobj (ssadd (entlast) currobj))
(setq coords (list 
(list 319.4375 -27.7293) 
(list 245.415 -27.7793) 
(list 245.415 -27.9563) 
(list 319.4375 -27.8063)))
(apply 'command (append '("pline") coords '("c")))
(setq currobj (ssadd (entlast) currobj))
(setq coords (list 
(list 319.4375 -27.9493) 
(list 245.415 -28.0993) 
(list 245.415 -28.2763) 
(list 319.4375 -28.0263)))
(apply 'command (append '("pline") coords '("c")))
(setq currobj (ssadd (entlast) currobj))
(setq coords (list 
(list 319.4375 -28.1693) 
(list 245.415 -28.4193) 
(list 245.415 -28.5963) 
(list 319.4375 -28.2463)))
(apply 'command (append '("pline") coords '("c")))
(setq currobj (ssadd (entlast) currobj))
(setq coords (list 
(list 319.4375 -28.3893) 
(list 245.415 -28.7393) 
(list 245.415 -28.9163) 
(list 319.4375 -28.4663)))
(apply 'command (append '("pline") coords '("c")))
(setq currobj (ssadd (entlast) currobj))
(setq coords (list 
(list 319.4375 -28.6093) 
(list 245.415 -29.0593) 
(list 245.415 -29.2363) 
(list 319.4375 -28.6863)))
(apply 'command (append '("pline") coords '("c")))
(setq currobj (ssadd (entlast) currobj))
(setq coords (list 
(list 319.4375 -28.8293) 
(list 245.415 -29.3793) 
(list 245.415 -29.5563) 
(list 319.4375 -28.9063)))
(apply 'command (append '("pline") coords '("c")))
(setq currobj (ssadd (entlast) currobj))
(setq coords (list 
(list 319.4375 -29.0493) 
(list 245.415 -29.6993) 
(list 245.415 -29.8763) 
(list 319.4375 -29.1263)))
(apply 'command (append '("pline") coords '("c")))
(setq currobj (ssadd (entlast) currobj))
(command "_layer" "set" "nitride" "")
(command "_layer" "set" "text" "")
(command "_circle" "319.0625,-40.2693" "0.075")
(command "_circle" "319.0625,-39.9693" "0.075")
(command "_circle" "319.0625,-39.6693" "0.075")
(command "_circle" "319.0625,-39.3693" "0.075")
(command "_circle" "319.0625,-39.0693" "0.075")
(command "_circle" "318.7625,-40.2693" "0.075")
(command "_circle" "318.7625,-39.9693" "0.075")
(command "_circle" "318.7625,-39.6693" "0.075")
(command "_circle" "318.7625,-39.3693" "0.075")
(command "_circle" "318.7625,-39.0693" "0.075")
(command "_circle" "318.4625,-40.2693" "0.075")
(command "_circle" "318.4625,-39.9693" "0.075")
(command "_circle" "318.4625,-39.6693" "0.075")
(command "_circle" "318.4625,-39.3693" "0.075")
(command "_circle" "318.4625,-39.0693" "0.075")
(command "_circle" "318.1625,-40.2693" "0.075")
(command "_circle" "318.1625,-39.9693" "0.075")
(command "_circle" "318.1625,-39.6693" "0.075")
(command "_circle" "318.1625,-39.3693" "0.075")
(command "_circle" "318.1625,-39.0693" "0.075")
(command "_circle" "317.8625,-40.2693" "0.075")
(command "_circle" "317.8625,-39.9693" "0.075")
(command "_circle" "317.8625,-39.6693" "0.075")
(command "_circle" "317.8625,-39.3693" "0.075")
(command "_circle" "317.8625,-39.0693" "0.075")
(command "_layer" "set" "nitride" "")
(setq coords (list 
(list 320.2625 -14.8263) 
(list 320.2625 100.8184) 
(list 319.7375 100.8184) 
(list 319.7375 -14.8263)))
(apply 'command (append '("pline") coords '("c")))
(setq currobj (ssadd (entlast) currobj))
(command "_layer" "set" "prebias" "")
(command "_rectangle" "319.7375,-14.8263" "320.2625,100.8184")
(setq currobj (ssadd (entlast) currobj))
(command "_layer" "set" "nitride" "")
(setq coords (list 
(list 320.2625 100.8184) 
(list 320.5625 110.8184) 
(list 320.5625 110.8184) 
(list 320.5625 111.8184) 
(list 394.585 111.0684) 
(list 394.585 116.0114) 
(list 320.5625 115.2614) 
(list 320.5625 116.2614) 
(list 320.5625 116.2614) 
(list 320.2625 126.2614) 
(list 319.7375 126.2614) 
(list 319.4375 116.2614) 
(list 319.4375 116.2614) 
(list 319.4375 115.2614) 
(list 245.415 116.0114) 
(list 245.415 111.0684) 
(list 319.4375 111.8184) 
(list 319.4375 110.8184) 
(list 319.4375 110.8184) 
(list 319.7375 100.8184)))
(apply 'command (append '("pline") coords '("c")))
(setq currobj (ssadd (entlast) currobj))
(command "_layer" "set" "prebias" "")
(setq coords (list 
(list 319.4375 100.8184) 
(list 319.4375 111.8184) 
(list 245.415 111.0684) 
(list 245.415 116.0114) 
(list 319.4375 115.2614) 
(list 319.4375 126.2614) 
(list 320.5625 126.2614) 
(list 320.5625 115.2614) 
(list 394.585 116.0114) 
(list 394.585 111.0684) 
(list 320.5625 111.8184) 
(list 320.5625 100.8184)))
(apply 'command (append '("pline") coords '("c")))
(setq currobj (ssadd (entlast) currobj))
(command "_layer" "set" "nitride" "")
(command "_layer" "set" "fda1" "")
(setq coords (list 
(list 320.5625 111.9614) 
(list 394.585 111.2114) 
(list 394.585 111.3884) 
(list 320.5625 112.0384)))
(apply 'command (append '("pline") coords '("c")))
(setq currobj (ssadd (entlast) currobj))
(setq coords (list 
(list 320.5625 112.1814) 
(list 394.585 111.5314) 
(list 394.585 111.7084) 
(list 320.5625 112.2584)))
(apply 'command (append '("pline") coords '("c")))
(setq currobj (ssadd (entlast) currobj))
(setq coords (list 
(list 320.5625 112.4014) 
(list 394.585 111.8514) 
(list 394.585 112.0284) 
(list 320.5625 112.4784)))
(apply 'command (append '("pline") coords '("c")))
(setq currobj (ssadd (entlast) currobj))
(setq coords (list 
(list 320.5625 112.6214) 
(list 394.585 112.1714) 
(list 394.585 112.3484) 
(list 320.5625 112.6984)))
(apply 'command (append '("pline") coords '("c")))
(setq currobj (ssadd (entlast) currobj))
(setq coords (list 
(list 320.5625 112.8414) 
(list 394.585 112.4914) 
(list 394.585 112.6684) 
(list 320.5625 112.9184)))
(apply 'command (append '("pline") coords '("c")))
(setq currobj (ssadd (entlast) currobj))
(setq coords (list 
(list 320.5625 113.0614) 
(list 394.585 112.8114) 
(list 394.585 112.9884) 
(list 320.5625 113.1384)))
(apply 'command (append '("pline") coords '("c")))
(setq currobj (ssadd (entlast) currobj))
(setq coords (list 
(list 320.5625 113.2814) 
(list 394.585 113.1314) 
(list 394.585 113.3084) 
(list 320.5625 113.3584)))
(apply 'command (append '("pline") coords '("c")))
(setq currobj (ssadd (entlast) currobj))
(setq coords (list 
(list 320.5625 113.5014) 
(list 394.585 113.4514) 
(list 394.585 113.6284) 
(list 320.5625 113.5784)))
(apply 'command (append '("pline") coords '("c")))
(setq currobj (ssadd (entlast) currobj))
(setq coords (list 
(list 320.5625 113.7214) 
(list 394.585 113.7714) 
(list 394.585 113.9484) 
(list 320.5625 113.7984)))
(apply 'command (append '("pline") coords '("c")))
(setq currobj (ssadd (entlast) currobj))
(setq coords (list 
(list 320.5625 113.9414) 
(list 394.585 114.0914) 
(list 394.585 114.2684) 
(list 320.5625 114.0184)))
(apply 'command (append '("pline") coords '("c")))
(setq currobj (ssadd (entlast) currobj))
(setq coords (list 
(list 320.5625 114.1614) 
(list 394.585 114.4114) 
(list 394.585 114.5884) 
(list 320.5625 114.2384)))
(apply 'command (append '("pline") coords '("c")))
(setq currobj (ssadd (entlast) currobj))
(setq coords (list 
(list 320.5625 114.3814) 
(list 394.585 114.7314) 
(list 394.585 114.9084) 
(list 320.5625 114.4584)))
(apply 'command (append '("pline") coords '("c")))
(setq currobj (ssadd (entlast) currobj))
(setq coords (list 
(list 320.5625 114.6014) 
(list 394.585 115.0514) 
(list 394.585 115.2284) 
(list 320.5625 114.6784)))
(apply 'command (append '("pline") coords '("c")))
(setq currobj (ssadd (entlast) currobj))
(setq coords (list 
(list 320.5625 114.8214) 
(list 394.585 115.3714) 
(list 394.585 115.5484) 
(list 320.5625 114.8984)))
(apply 'command (append '("pline") coords '("c")))
(setq currobj (ssadd (entlast) currobj))
(setq coords (list 
(list 320.5625 115.0414) 
(list 394.585 115.6914) 
(list 394.585 115.8684) 
(list 320.5625 115.1184)))
(apply 'command (append '("pline") coords '("c")))
(setq currobj (ssadd (entlast) currobj))
(setq coords (list 
(list 319.4375 115.1184) 
(list 245.415 115.8684) 
(list 245.415 115.6914) 
(list 319.4375 115.0414)))
(apply 'command (append '("pline") coords '("c")))
(setq currobj (ssadd (entlast) currobj))
(setq coords (list 
(list 319.4375 114.8984) 
(list 245.415 115.5484) 
(list 245.415 115.3714) 
(list 319.4375 114.8214)))
(apply 'command (append '("pline") coords '("c")))
(setq currobj (ssadd (entlast) currobj))
(setq coords (list 
(list 319.4375 114.6784) 
(list 245.415 115.2284) 
(list 245.415 115.0514) 
(list 319.4375 114.6014)))
(apply 'command (append '("pline") coords '("c")))
(setq currobj (ssadd (entlast) currobj))
(setq coords (list 
(list 319.4375 114.4584) 
(list 245.415 114.9084) 
(list 245.415 114.7314) 
(list 319.4375 114.3814)))
(apply 'command (append '("pline") coords '("c")))
(setq currobj (ssadd (entlast) currobj))
(setq coords (list 
(list 319.4375 114.2384) 
(list 245.415 114.5884) 
(list 245.415 114.4114) 
(list 319.4375 114.1614)))
(apply 'command (append '("pline") coords '("c")))
(setq currobj (ssadd (entlast) currobj))
(setq coords (list 
(list 319.4375 114.0184) 
(list 245.415 114.2684) 
(list 245.415 114.0914) 
(list 319.4375 113.9414)))
(apply 'command (append '("pline") coords '("c")))
(setq currobj (ssadd (entlast) currobj))
(setq coords (list 
(list 319.4375 113.7984) 
(list 245.415 113.9484) 
(list 245.415 113.7714) 
(list 319.4375 113.7214)))
(apply 'command (append '("pline") coords '("c")))
(setq currobj (ssadd (entlast) currobj))
(setq coords (list 
(list 319.4375 113.5784) 
(list 245.415 113.6284) 
(list 245.415 113.4514) 
(list 319.4375 113.5014)))
(apply 'command (append '("pline") coords '("c")))
(setq currobj (ssadd (entlast) currobj))
(setq coords (list 
(list 319.4375 113.3584) 
(list 245.415 113.3084) 
(list 245.415 113.1314) 
(list 319.4375 113.2814)))
(apply 'command (append '("pline") coords '("c")))
(setq currobj (ssadd (entlast) currobj))
(setq coords (list 
(list 319.4375 113.1384) 
(list 245.415 112.9884) 
(list 245.415 112.8114) 
(list 319.4375 113.0614)))
(apply 'command (append '("pline") coords '("c")))
(setq currobj (ssadd (entlast) currobj))
(setq coords (list 
(list 319.4375 112.9184) 
(list 245.415 112.6684) 
(list 245.415 112.4914) 
(list 319.4375 112.8414)))
(apply 'command (append '("pline") coords '("c")))
(setq currobj (ssadd (entlast) currobj))
(setq coords (list 
(list 319.4375 112.6984) 
(list 245.415 112.3484) 
(list 245.415 112.1714) 
(list 319.4375 112.6214)))
(apply 'command (append '("pline") coords '("c")))
(setq currobj (ssadd (entlast) currobj))
(setq coords (list 
(list 319.4375 112.4784) 
(list 245.415 112.0284) 
(list 245.415 111.8514) 
(list 319.4375 112.4014)))
(apply 'command (append '("pline") coords '("c")))
(setq currobj (ssadd (entlast) currobj))
(setq coords (list 
(list 319.4375 112.2584) 
(list 245.415 111.7084) 
(list 245.415 111.5314) 
(list 319.4375 112.1814)))
(apply 'command (append '("pline") coords '("c")))
(setq currobj (ssadd (entlast) currobj))
(setq coords (list 
(list 319.4375 112.0384) 
(list 245.415 111.3884) 
(list 245.415 111.2114) 
(list 319.4375 111.9614)))
(apply 'command (append '("pline") coords '("c")))
(setq currobj (ssadd (entlast) currobj))
(command "_layer" "set" "nitride" "")
(command "_layer" "set" "text" "")
(command "_circle" "319.0625,100.8184" "0.075")
(command "_circle" "319.0625,101.1184" "0.075")
(command "_circle" "319.0625,101.4184" "0.075")
(command "_circle" "319.0625,101.7184" "0.075")
(command "_circle" "319.0625,102.0184" "0.075")
(command "_circle" "318.7625,100.8184" "0.075")
(command "_circle" "318.7625,101.1184" "0.075")
(command "_circle" "318.7625,101.4184" "0.075")
(command "_circle" "318.7625,101.7184" "0.075")
(command "_circle" "318.7625,102.0184" "0.075")
(command "_circle" "318.4625,100.8184" "0.075")
(command "_circle" "318.4625,101.1184" "0.075")
(command "_circle" "318.4625,101.4184" "0.075")
(command "_circle" "318.4625,101.7184" "0.075")
(command "_circle" "318.4625,102.0184" "0.075")
(command "_circle" "318.1625,100.8184" "0.075")
(command "_circle" "318.1625,101.1184" "0.075")
(command "_circle" "318.1625,101.4184" "0.075")
(command "_circle" "318.1625,101.7184" "0.075")
(command "_circle" "318.1625,102.0184" "0.075")
(command "_circle" "317.8625,100.8184" "0.075")
(command "_circle" "317.8625,101.1184" "0.075")
(command "_circle" "317.8625,101.4184" "0.075")
(command "_circle" "317.8625,101.7184" "0.075")
(command "_circle" "317.8625,102.0184" "0.075")
(command "_layer" "set" "nitride" "")
(setq coords (list 
(list 320.2625 126.2614) 
(list 320.2625 241.9061) 
(list 319.7375 241.9061) 
(list 319.7375 126.2614)))
(apply 'command (append '("pline") coords '("c")))
(setq currobj (ssadd (entlast) currobj))
(command "_layer" "set" "prebias" "")
(command "_rectangle" "319.7375,126.2614" "320.2625,241.9061")
(setq currobj (ssadd (entlast) currobj))
(command "_layer" "set" "nitride" "")
(setq coords (list 
(list 320.2625 241.9061) 
(list 320.5625 251.9061) 
(list 320.5625 251.9061) 
(list 320.5625 252.9061) 
(list 394.585 252.1561) 
(list 394.585 257.0991) 
(list 320.5625 256.3491) 
(list 320.5625 257.3491) 
(list 320.5625 257.3491) 
(list 320.2625 267.3491) 
(list 319.7375 267.3491) 
(list 319.4375 257.3491) 
(list 319.4375 257.3491) 
(list 319.4375 256.3491) 
(list 245.415 257.0991) 
(list 245.415 252.1561) 
(list 319.4375 252.9061) 
(list 319.4375 251.9061) 
(list 319.4375 251.9061) 
(list 319.7375 241.9061)))
(apply 'command (append '("pline") coords '("c")))
(setq currobj (ssadd (entlast) currobj))
(command "_layer" "set" "prebias" "")
(setq coords (list 
(list 319.4375 241.9061) 
(list 319.4375 252.9061) 
(list 245.415 252.1561) 
(list 245.415 257.0991) 
(list 319.4375 256.3491) 
(list 319.4375 267.3491) 
(list 320.5625 267.3491) 
(list 320.5625 256.3491) 
(list 394.585 257.0991) 
(list 394.585 252.1561) 
(list 320.5625 252.9061) 
(list 320.5625 241.9061)))
(apply 'command (append '("pline") coords '("c")))
(setq currobj (ssadd (entlast) currobj))
(command "_layer" "set" "nitride" "")
(command "_layer" "set" "fda1" "")
(setq coords (list 
(list 320.5625 253.0491) 
(list 394.585 252.2991) 
(list 394.585 252.4761) 
(list 320.5625 253.1261)))
(apply 'command (append '("pline") coords '("c")))
(setq currobj (ssadd (entlast) currobj))
(setq coords (list 
(list 320.5625 253.2691) 
(list 394.585 252.6191) 
(list 394.585 252.7961) 
(list 320.5625 253.3461)))
(apply 'command (append '("pline") coords '("c")))
(setq currobj (ssadd (entlast) currobj))
(setq coords (list 
(list 320.5625 253.4891) 
(list 394.585 252.9391) 
(list 394.585 253.1161) 
(list 320.5625 253.5661)))
(apply 'command (append '("pline") coords '("c")))
(setq currobj (ssadd (entlast) currobj))
(setq coords (list 
(list 320.5625 253.7091) 
(list 394.585 253.2591) 
(list 394.585 253.4361) 
(list 320.5625 253.7861)))
(apply 'command (append '("pline") coords '("c")))
(setq currobj (ssadd (entlast) currobj))
(setq coords (list 
(list 320.5625 253.9291) 
(list 394.585 253.5791) 
(list 394.585 253.7561) 
(list 320.5625 254.0061)))
(apply 'command (append '("pline") coords '("c")))
(setq currobj (ssadd (entlast) currobj))
(setq coords (list 
(list 320.5625 254.1491) 
(list 394.585 253.8991) 
(list 394.585 254.0761) 
(list 320.5625 254.2261)))
(apply 'command (append '("pline") coords '("c")))
(setq currobj (ssadd (entlast) currobj))
(setq coords (list 
(list 320.5625 254.3691) 
(list 394.585 254.2191) 
(list 394.585 254.3961) 
(list 320.5625 254.4461)))
(apply 'command (append '("pline") coords '("c")))
(setq currobj (ssadd (entlast) currobj))
(setq coords (list 
(list 320.5625 254.5891) 
(list 394.585 254.5391) 
(list 394.585 254.7161) 
(list 320.5625 254.6661)))
(apply 'command (append '("pline") coords '("c")))
(setq currobj (ssadd (entlast) currobj))
(setq coords (list 
(list 320.5625 254.8091) 
(list 394.585 254.8591) 
(list 394.585 255.0361) 
(list 320.5625 254.8861)))
(apply 'command (append '("pline") coords '("c")))
(setq currobj (ssadd (entlast) currobj))
(setq coords (list 
(list 320.5625 255.0291) 
(list 394.585 255.1791) 
(list 394.585 255.3561) 
(list 320.5625 255.1061)))
(apply 'command (append '("pline") coords '("c")))
(setq currobj (ssadd (entlast) currobj))
(setq coords (list 
(list 320.5625 255.2491) 
(list 394.585 255.4991) 
(list 394.585 255.6761) 
(list 320.5625 255.3261)))
(apply 'command (append '("pline") coords '("c")))
(setq currobj (ssadd (entlast) currobj))
(setq coords (list 
(list 320.5625 255.4691) 
(list 394.585 255.8191) 
(list 394.585 255.9961) 
(list 320.5625 255.5461)))
(apply 'command (append '("pline") coords '("c")))
(setq currobj (ssadd (entlast) currobj))
(setq coords (list 
(list 320.5625 255.6891) 
(list 394.585 256.1391) 
(list 394.585 256.3161) 
(list 320.5625 255.7661)))
(apply 'command (append '("pline") coords '("c")))
(setq currobj (ssadd (entlast) currobj))
(setq coords (list 
(list 320.5625 255.9091) 
(list 394.585 256.4591) 
(list 394.585 256.6361) 
(list 320.5625 255.9861)))
(apply 'command (append '("pline") coords '("c")))
(setq currobj (ssadd (entlast) currobj))
(setq coords (list 
(list 320.5625 256.1291) 
(list 394.585 256.7791) 
(list 394.585 256.9561) 
(list 320.5625 256.2061)))
(apply 'command (append '("pline") coords '("c")))
(setq currobj (ssadd (entlast) currobj))
(setq coords (list 
(list 319.4375 256.2061) 
(list 245.415 256.9561) 
(list 245.415 256.7791) 
(list 319.4375 256.1291)))
(apply 'command (append '("pline") coords '("c")))
(setq currobj (ssadd (entlast) currobj))
(setq coords (list 
(list 319.4375 255.9861) 
(list 245.415 256.6361) 
(list 245.415 256.4591) 
(list 319.4375 255.9091)))
(apply 'command (append '("pline") coords '("c")))
(setq currobj (ssadd (entlast) currobj))
(setq coords (list 
(list 319.4375 255.7661) 
(list 245.415 256.3161) 
(list 245.415 256.1391) 
(list 319.4375 255.6891)))
(apply 'command (append '("pline") coords '("c")))
(setq currobj (ssadd (entlast) currobj))
(setq coords (list 
(list 319.4375 255.5461) 
(list 245.415 255.9961) 
(list 245.415 255.8191) 
(list 319.4375 255.4691)))
(apply 'command (append '("pline") coords '("c")))
(setq currobj (ssadd (entlast) currobj))
(setq coords (list 
(list 319.4375 255.3261) 
(list 245.415 255.6761) 
(list 245.415 255.4991) 
(list 319.4375 255.2491)))
(apply 'command (append '("pline") coords '("c")))
(setq currobj (ssadd (entlast) currobj))
(setq coords (list 
(list 319.4375 255.1061) 
(list 245.415 255.3561) 
(list 245.415 255.1791) 
(list 319.4375 255.0291)))
(apply 'command (append '("pline") coords '("c")))
(setq currobj (ssadd (entlast) currobj))
(setq coords (list 
(list 319.4375 254.8861) 
(list 245.415 255.0361) 
(list 245.415 254.8591) 
(list 319.4375 254.8091)))
(apply 'command (append '("pline") coords '("c")))
(setq currobj (ssadd (entlast) currobj))
(setq coords (list 
(list 319.4375 254.6661) 
(list 245.415 254.7161) 
(list 245.415 254.5391) 
(list 319.4375 254.5891)))
(apply 'command (append '("pline") coords '("c")))
(setq currobj (ssadd (entlast) currobj))
(setq coords (list 
(list 319.4375 254.4461) 
(list 245.415 254.3961) 
(list 245.415 254.2191) 
(list 319.4375 254.3691)))
(apply 'command (append '("pline") coords '("c")))
(setq currobj (ssadd (entlast) currobj))
(setq coords (list 
(list 319.4375 254.2261) 
(list 245.415 254.0761) 
(list 245.415 253.8991) 
(list 319.4375 254.1491)))
(apply 'command (append '("pline") coords '("c")))
(setq currobj (ssadd (entlast) currobj))
(setq coords (list 
(list 319.4375 254.0061) 
(list 245.415 253.7561) 
(list 245.415 253.5791) 
(list 319.4375 253.9291)))
(apply 'command (append '("pline") coords '("c")))
(setq currobj (ssadd (entlast) currobj))
(setq coords (list 
(list 319.4375 253.7861) 
(list 245.415 253.4361) 
(list 245.415 253.2591) 
(list 319.4375 253.7091)))
(apply 'command (append '("pline") coords '("c")))
(setq currobj (ssadd (entlast) currobj))
(setq coords (list 
(list 319.4375 253.5661) 
(list 245.415 253.1161) 
(list 245.415 252.9391) 
(list 319.4375 253.4891)))
(apply 'command (append '("pline") coords '("c")))
(setq currobj (ssadd (entlast) currobj))
(setq coords (list 
(list 319.4375 253.3461) 
(list 245.415 252.7961) 
(list 245.415 252.6191) 
(list 319.4375 253.2691)))
(apply 'command (append '("pline") coords '("c")))
(setq currobj (ssadd (entlast) currobj))
(setq coords (list 
(list 319.4375 253.1261) 
(list 245.415 252.4761) 
(list 245.415 252.2991) 
(list 319.4375 253.0491)))
(apply 'command (append '("pline") coords '("c")))
(setq currobj (ssadd (entlast) currobj))
(command "_layer" "set" "nitride" "")
(command "_layer" "set" "text" "")
(command "_circle" "319.0625,241.9061" "0.075")
(command "_circle" "319.0625,242.2061" "0.075")
(command "_circle" "319.0625,242.5061" "0.075")
(command "_circle" "319.0625,242.8061" "0.075")
(command "_circle" "319.0625,243.1061" "0.075")
(command "_circle" "318.7625,241.9061" "0.075")
(command "_circle" "318.7625,242.2061" "0.075")
(command "_circle" "318.7625,242.5061" "0.075")
(command "_circle" "318.7625,242.8061" "0.075")
(command "_circle" "318.7625,243.1061" "0.075")
(command "_circle" "318.4625,241.9061" "0.075")
(command "_circle" "318.4625,242.2061" "0.075")
(command "_circle" "318.4625,242.5061" "0.075")
(command "_circle" "318.4625,242.8061" "0.075")
(command "_circle" "318.4625,243.1061" "0.075")
(command "_circle" "318.1625,241.9061" "0.075")
(command "_circle" "318.1625,242.2061" "0.075")
(command "_circle" "318.1625,242.5061" "0.075")
(command "_circle" "318.1625,242.8061" "0.075")
(command "_circle" "318.1625,243.1061" "0.075")
(command "_circle" "317.8625,241.9061" "0.075")
(command "_circle" "317.8625,242.2061" "0.075")
(command "_circle" "317.8625,242.5061" "0.075")
(command "_circle" "317.8625,242.8061" "0.075")
(command "_circle" "317.8625,243.1061" "0.075")
(command "_layer" "set" "nitride" "")
(setq coords (list 
(list 320.2625 267.3491) 
(list 320.2625 382.9939) 
(list 319.7375 382.9939) 
(list 319.7375 267.3491)))
(apply 'command (append '("pline") coords '("c")))
(setq currobj (ssadd (entlast) currobj))
(command "_layer" "set" "prebias" "")
(command "_rectangle" "319.7375,267.3491" "320.2625,382.9939")
(setq currobj (ssadd (entlast) currobj))
(command "_layer" "set" "nitride" "")
(setq coords (list 
(list 320.2625 382.9939) 
(list 320.5625 392.9939) 
(list 320.5625 392.9939) 
(list 320.5625 393.9939) 
(list 394.585 393.2439) 
(list 394.585 398.1869) 
(list 320.5625 397.4369) 
(list 320.5625 398.4369) 
(list 320.5625 398.4369) 
(list 320.2625 408.4369) 
(list 319.7375 408.4369) 
(list 319.4375 398.4369) 
(list 319.4375 398.4369) 
(list 319.4375 397.4369) 
(list 245.415 398.1869) 
(list 245.415 393.2439) 
(list 319.4375 393.9939) 
(list 319.4375 392.9939) 
(list 319.4375 392.9939) 
(list 319.7375 382.9939)))
(apply 'command (append '("pline") coords '("c")))
(setq currobj (ssadd (entlast) currobj))
(command "_layer" "set" "prebias" "")
(setq coords (list 
(list 319.4375 382.9939) 
(list 319.4375 393.9939) 
(list 245.415 393.2439) 
(list 245.415 398.1869) 
(list 319.4375 397.4369) 
(list 319.4375 408.4369) 
(list 320.5625 408.4369) 
(list 320.5625 397.4369) 
(list 394.585 398.1869) 
(list 394.585 393.2439) 
(list 320.5625 393.9939) 
(list 320.5625 382.9939)))
(apply 'command (append '("pline") coords '("c")))
(setq currobj (ssadd (entlast) currobj))
(command "_layer" "set" "nitride" "")
(command "_layer" "set" "fda1" "")
(setq coords (list 
(list 320.5625 394.1369) 
(list 394.585 393.3869) 
(list 394.585 393.5639) 
(list 320.5625 394.2139)))
(apply 'command (append '("pline") coords '("c")))
(setq currobj (ssadd (entlast) currobj))
(setq coords (list 
(list 320.5625 394.3569) 
(list 394.585 393.7069) 
(list 394.585 393.8839) 
(list 320.5625 394.4339)))
(apply 'command (append '("pline") coords '("c")))
(setq currobj (ssadd (entlast) currobj))
(setq coords (list 
(list 320.5625 394.5769) 
(list 394.585 394.0269) 
(list 394.585 394.2039) 
(list 320.5625 394.6539)))
(apply 'command (append '("pline") coords '("c")))
(setq currobj (ssadd (entlast) currobj))
(setq coords (list 
(list 320.5625 394.7969) 
(list 394.585 394.3469) 
(list 394.585 394.5239) 
(list 320.5625 394.8739)))
(apply 'command (append '("pline") coords '("c")))
(setq currobj (ssadd (entlast) currobj))
(setq coords (list 
(list 320.5625 395.0169) 
(list 394.585 394.6669) 
(list 394.585 394.8439) 
(list 320.5625 395.0939)))
(apply 'command (append '("pline") coords '("c")))
(setq currobj (ssadd (entlast) currobj))
(setq coords (list 
(list 320.5625 395.2369) 
(list 394.585 394.9869) 
(list 394.585 395.1639) 
(list 320.5625 395.3139)))
(apply 'command (append '("pline") coords '("c")))
(setq currobj (ssadd (entlast) currobj))
(setq coords (list 
(list 320.5625 395.4569) 
(list 394.585 395.3069) 
(list 394.585 395.4839) 
(list 320.5625 395.5339)))
(apply 'command (append '("pline") coords '("c")))
(setq currobj (ssadd (entlast) currobj))
(setq coords (list 
(list 320.5625 395.6769) 
(list 394.585 395.6269) 
(list 394.585 395.8039) 
(list 320.5625 395.7539)))
(apply 'command (append '("pline") coords '("c")))
(setq currobj (ssadd (entlast) currobj))
(setq coords (list 
(list 320.5625 395.8969) 
(list 394.585 395.9469) 
(list 394.585 396.1239) 
(list 320.5625 395.9739)))
(apply 'command (append '("pline") coords '("c")))
(setq currobj (ssadd (entlast) currobj))
(setq coords (list 
(list 320.5625 396.1169) 
(list 394.585 396.2669) 
(list 394.585 396.4439) 
(list 320.5625 396.1939)))
(apply 'command (append '("pline") coords '("c")))
(setq currobj (ssadd (entlast) currobj))
(setq coords (list 
(list 320.5625 396.3369) 
(list 394.585 396.5869) 
(list 394.585 396.7639) 
(list 320.5625 396.4139)))
(apply 'command (append '("pline") coords '("c")))
(setq currobj (ssadd (entlast) currobj))
(setq coords (list 
(list 320.5625 396.5569) 
(list 394.585 396.9069) 
(list 394.585 397.0839) 
(list 320.5625 396.6339)))
(apply 'command (append '("pline") coords '("c")))
(setq currobj (ssadd (entlast) currobj))
(setq coords (list 
(list 320.5625 396.7769) 
(list 394.585 397.2269) 
(list 394.585 397.4039) 
(list 320.5625 396.8539)))
(apply 'command (append '("pline") coords '("c")))
(setq currobj (ssadd (entlast) currobj))
(setq coords (list 
(list 320.5625 396.9969) 
(list 394.585 397.5469) 
(list 394.585 397.7239) 
(list 320.5625 397.0739)))
(apply 'command (append '("pline") coords '("c")))
(setq currobj (ssadd (entlast) currobj))
(setq coords (list 
(list 320.5625 397.2169) 
(list 394.585 397.8669) 
(list 394.585 398.0439) 
(list 320.5625 397.2939)))
(apply 'command (append '("pline") coords '("c")))
(setq currobj (ssadd (entlast) currobj))
(setq coords (list 
(list 319.4375 397.2939) 
(list 245.415 398.0439) 
(list 245.415 397.8669) 
(list 319.4375 397.2169)))
(apply 'command (append '("pline") coords '("c")))
(setq currobj (ssadd (entlast) currobj))
(setq coords (list 
(list 319.4375 397.0739) 
(list 245.415 397.7239) 
(list 245.415 397.5469) 
(list 319.4375 396.9969)))
(apply 'command (append '("pline") coords '("c")))
(setq currobj (ssadd (entlast) currobj))
(setq coords (list 
(list 319.4375 396.8539) 
(list 245.415 397.4039) 
(list 245.415 397.2269) 
(list 319.4375 396.7769)))
(apply 'command (append '("pline") coords '("c")))
(setq currobj (ssadd (entlast) currobj))
(setq coords (list 
(list 319.4375 396.6339) 
(list 245.415 397.0839) 
(list 245.415 396.9069) 
(list 319.4375 396.5569)))
(apply 'command (append '("pline") coords '("c")))
(setq currobj (ssadd (entlast) currobj))
(setq coords (list 
(list 319.4375 396.4139) 
(list 245.415 396.7639) 
(list 245.415 396.5869) 
(list 319.4375 396.3369)))
(apply 'command (append '("pline") coords '("c")))
(setq currobj (ssadd (entlast) currobj))
(setq coords (list 
(list 319.4375 396.1939) 
(list 245.415 396.4439) 
(list 245.415 396.2669) 
(list 319.4375 396.1169)))
(apply 'command (append '("pline") coords '("c")))
(setq currobj (ssadd (entlast) currobj))
(setq coords (list 
(list 319.4375 395.9739) 
(list 245.415 396.1239) 
(list 245.415 395.9469) 
(list 319.4375 395.8969)))
(apply 'command (append '("pline") coords '("c")))
(setq currobj (ssadd (entlast) currobj))
(setq coords (list 
(list 319.4375 395.7539) 
(list 245.415 395.8039) 
(list 245.415 395.6269) 
(list 319.4375 395.6769)))
(apply 'command (append '("pline") coords '("c")))
(setq currobj (ssadd (entlast) currobj))
(setq coords (list 
(list 319.4375 395.5339) 
(list 245.415 395.4839) 
(list 245.415 395.3069) 
(list 319.4375 395.4569)))
(apply 'command (append '("pline") coords '("c")))
(setq currobj (ssadd (entlast) currobj))
(setq coords (list 
(list 319.4375 395.3139) 
(list 245.415 395.1639) 
(list 245.415 394.9869) 
(list 319.4375 395.2369)))
(apply 'command (append '("pline") coords '("c")))
(setq currobj (ssadd (entlast) currobj))
(setq coords (list 
(list 319.4375 395.0939) 
(list 245.415 394.8439) 
(list 245.415 394.6669) 
(list 319.4375 395.0169)))
(apply 'command (append '("pline") coords '("c")))
(setq currobj (ssadd (entlast) currobj))
(setq coords (list 
(list 319.4375 394.8739) 
(list 245.415 394.5239) 
(list 245.415 394.3469) 
(list 319.4375 394.7969)))
(apply 'command (append '("pline") coords '("c")))
(setq currobj (ssadd (entlast) currobj))
(setq coords (list 
(list 319.4375 394.6539) 
(list 245.415 394.2039) 
(list 245.415 394.0269) 
(list 319.4375 394.5769)))
(apply 'command (append '("pline") coords '("c")))
(setq currobj (ssadd (entlast) currobj))
(setq coords (list 
(list 319.4375 394.4339) 
(list 245.415 393.8839) 
(list 245.415 393.7069) 
(list 319.4375 394.3569)))
(apply 'command (append '("pline") coords '("c")))
(setq currobj (ssadd (entlast) currobj))
(setq coords (list 
(list 319.4375 394.2139) 
(list 245.415 393.5639) 
(list 245.415 393.3869) 
(list 319.4375 394.1369)))
(apply 'command (append '("pline") coords '("c")))
(setq currobj (ssadd (entlast) currobj))
(command "_layer" "set" "nitride" "")
(command "_layer" "set" "text" "")
(command "_circle" "319.0625,382.9939" "0.075")
(command "_circle" "319.0625,383.2939" "0.075")
(command "_circle" "319.0625,383.5939" "0.075")
(command "_circle" "319.0625,383.8939" "0.075")
(command "_circle" "319.0625,384.1939" "0.075")
(command "_circle" "318.7625,382.9939" "0.075")
(command "_circle" "318.7625,383.2939" "0.075")
(command "_circle" "318.7625,383.5939" "0.075")
(command "_circle" "318.7625,383.8939" "0.075")
(command "_circle" "318.7625,384.1939" "0.075")
(command "_circle" "318.4625,382.9939" "0.075")
(command "_circle" "318.4625,383.2939" "0.075")
(command "_circle" "318.4625,383.5939" "0.075")
(command "_circle" "318.4625,383.8939" "0.075")
(command "_circle" "318.4625,384.1939" "0.075")
(command "_circle" "318.1625,382.9939" "0.075")
(command "_circle" "318.1625,383.2939" "0.075")
(command "_circle" "318.1625,383.5939" "0.075")
(command "_circle" "318.1625,383.8939" "0.075")
(command "_circle" "318.1625,384.1939" "0.075")
(command "_circle" "317.8625,382.9939" "0.075")
(command "_circle" "317.8625,383.2939" "0.075")
(command "_circle" "317.8625,383.5939" "0.075")
(command "_circle" "317.8625,383.8939" "0.075")
(command "_circle" "317.8625,384.1939" "0.075")
(command "_layer" "set" "nitride" "")
(setq coords (list 
(list 320.2625 408.4369) 
(list 320.2625 524.0816) 
(list 319.7375 524.0816) 
(list 319.7375 408.4369)))
(apply 'command (append '("pline") coords '("c")))
(setq currobj (ssadd (entlast) currobj))
(command "_layer" "set" "prebias" "")
(command "_rectangle" "319.7375,408.4369" "320.2625,524.0816")
(setq currobj (ssadd (entlast) currobj))
(command "_layer" "set" "nitride" "")
(setq coords (list 
(list 320.2625 524.0816) 
(list 320.5625 534.0816) 
(list 320.5625 534.0816) 
(list 320.5625 535.0816) 
(list 394.585 534.3316) 
(list 394.585 539.2746) 
(list 320.5625 538.5246) 
(list 320.5625 539.5246) 
(list 320.5625 539.5246) 
(list 320.2625 549.5246) 
(list 319.7375 549.5246) 
(list 319.4375 539.5246) 
(list 319.4375 539.5246) 
(list 319.4375 538.5246) 
(list 245.415 539.2746) 
(list 245.415 534.3316) 
(list 319.4375 535.0816) 
(list 319.4375 534.0816) 
(list 319.4375 534.0816) 
(list 319.7375 524.0816)))
(apply 'command (append '("pline") coords '("c")))
(setq currobj (ssadd (entlast) currobj))
(command "_layer" "set" "prebias" "")
(setq coords (list 
(list 319.4375 524.0816) 
(list 319.4375 535.0816) 
(list 245.415 534.3316) 
(list 245.415 539.2746) 
(list 319.4375 538.5246) 
(list 319.4375 549.5246) 
(list 320.5625 549.5246) 
(list 320.5625 538.5246) 
(list 394.585 539.2746) 
(list 394.585 534.3316) 
(list 320.5625 535.0816) 
(list 320.5625 524.0816)))
(apply 'command (append '("pline") coords '("c")))
(setq currobj (ssadd (entlast) currobj))
(command "_layer" "set" "nitride" "")
(command "_layer" "set" "fda1" "")
(setq coords (list 
(list 320.5625 535.2246) 
(list 394.585 534.4746) 
(list 394.585 534.6516) 
(list 320.5625 535.3016)))
(apply 'command (append '("pline") coords '("c")))
(setq currobj (ssadd (entlast) currobj))
(setq coords (list 
(list 320.5625 535.4446) 
(list 394.585 534.7946) 
(list 394.585 534.9716) 
(list 320.5625 535.5216)))
(apply 'command (append '("pline") coords '("c")))
(setq currobj (ssadd (entlast) currobj))
(setq coords (list 
(list 320.5625 535.6646) 
(list 394.585 535.1146) 
(list 394.585 535.2916) 
(list 320.5625 535.7416)))
(apply 'command (append '("pline") coords '("c")))
(setq currobj (ssadd (entlast) currobj))
(setq coords (list 
(list 320.5625 535.8846) 
(list 394.585 535.4346) 
(list 394.585 535.6116) 
(list 320.5625 535.9616)))
(apply 'command (append '("pline") coords '("c")))
(setq currobj (ssadd (entlast) currobj))
(setq coords (list 
(list 320.5625 536.1046) 
(list 394.585 535.7546) 
(list 394.585 535.9316) 
(list 320.5625 536.1816)))
(apply 'command (append '("pline") coords '("c")))
(setq currobj (ssadd (entlast) currobj))
(setq coords (list 
(list 320.5625 536.3246) 
(list 394.585 536.0746) 
(list 394.585 536.2516) 
(list 320.5625 536.4016)))
(apply 'command (append '("pline") coords '("c")))
(setq currobj (ssadd (entlast) currobj))
(setq coords (list 
(list 320.5625 536.5446) 
(list 394.585 536.3946) 
(list 394.585 536.5716) 
(list 320.5625 536.6216)))
(apply 'command (append '("pline") coords '("c")))
(setq currobj (ssadd (entlast) currobj))
(setq coords (list 
(list 320.5625 536.7646) 
(list 394.585 536.7146) 
(list 394.585 536.8916) 
(list 320.5625 536.8416)))
(apply 'command (append '("pline") coords '("c")))
(setq currobj (ssadd (entlast) currobj))
(setq coords (list 
(list 320.5625 536.9846) 
(list 394.585 537.0346) 
(list 394.585 537.2116) 
(list 320.5625 537.0616)))
(apply 'command (append '("pline") coords '("c")))
(setq currobj (ssadd (entlast) currobj))
(setq coords (list 
(list 320.5625 537.2046) 
(list 394.585 537.3546) 
(list 394.585 537.5316) 
(list 320.5625 537.2816)))
(apply 'command (append '("pline") coords '("c")))
(setq currobj (ssadd (entlast) currobj))
(setq coords (list 
(list 320.5625 537.4246) 
(list 394.585 537.6746) 
(list 394.585 537.8516) 
(list 320.5625 537.5016)))
(apply 'command (append '("pline") coords '("c")))
(setq currobj (ssadd (entlast) currobj))
(setq coords (list 
(list 320.5625 537.6446) 
(list 394.585 537.9946) 
(list 394.585 538.1716) 
(list 320.5625 537.7216)))
(apply 'command (append '("pline") coords '("c")))
(setq currobj (ssadd (entlast) currobj))
(setq coords (list 
(list 320.5625 537.8646) 
(list 394.585 538.3146) 
(list 394.585 538.4916) 
(list 320.5625 537.9416)))
(apply 'command (append '("pline") coords '("c")))
(setq currobj (ssadd (entlast) currobj))
(setq coords (list 
(list 320.5625 538.0846) 
(list 394.585 538.6346) 
(list 394.585 538.8116) 
(list 320.5625 538.1616)))
(apply 'command (append '("pline") coords '("c")))
(setq currobj (ssadd (entlast) currobj))
(setq coords (list 
(list 320.5625 538.3046) 
(list 394.585 538.9546) 
(list 394.585 539.1316) 
(list 320.5625 538.3816)))
(apply 'command (append '("pline") coords '("c")))
(setq currobj (ssadd (entlast) currobj))
(setq coords (list 
(list 319.4375 538.3816) 
(list 245.415 539.1316) 
(list 245.415 538.9546) 
(list 319.4375 538.3046)))
(apply 'command (append '("pline") coords '("c")))
(setq currobj (ssadd (entlast) currobj))
(setq coords (list 
(list 319.4375 538.1616) 
(list 245.415 538.8116) 
(list 245.415 538.6346) 
(list 319.4375 538.0846)))
(apply 'command (append '("pline") coords '("c")))
(setq currobj (ssadd (entlast) currobj))
(setq coords (list 
(list 319.4375 537.9416) 
(list 245.415 538.4916) 
(list 245.415 538.3146) 
(list 319.4375 537.8646)))
(apply 'command (append '("pline") coords '("c")))
(setq currobj (ssadd (entlast) currobj))
(setq coords (list 
(list 319.4375 537.7216) 
(list 245.415 538.1716) 
(list 245.415 537.9946) 
(list 319.4375 537.6446)))
(apply 'command (append '("pline") coords '("c")))
(setq currobj (ssadd (entlast) currobj))
(setq coords (list 
(list 319.4375 537.5016) 
(list 245.415 537.8516) 
(list 245.415 537.6746) 
(list 319.4375 537.4246)))
(apply 'command (append '("pline") coords '("c")))
(setq currobj (ssadd (entlast) currobj))
(setq coords (list 
(list 319.4375 537.2816) 
(list 245.415 537.5316) 
(list 245.415 537.3546) 
(list 319.4375 537.2046)))
(apply 'command (append '("pline") coords '("c")))
(setq currobj (ssadd (entlast) currobj))
(setq coords (list 
(list 319.4375 537.0616) 
(list 245.415 537.2116) 
(list 245.415 537.0346) 
(list 319.4375 536.9846)))
(apply 'command (append '("pline") coords '("c")))
(setq currobj (ssadd (entlast) currobj))
(setq coords (list 
(list 319.4375 536.8416) 
(list 245.415 536.8916) 
(list 245.415 536.7146) 
(list 319.4375 536.7646)))
(apply 'command (append '("pline") coords '("c")))
(setq currobj (ssadd (entlast) currobj))
(setq coords (list 
(list 319.4375 536.6216) 
(list 245.415 536.5716) 
(list 245.415 536.3946) 
(list 319.4375 536.5446)))
(apply 'command (append '("pline") coords '("c")))
(setq currobj (ssadd (entlast) currobj))
(setq coords (list 
(list 319.4375 536.4016) 
(list 245.415 536.2516) 
(list 245.415 536.0746) 
(list 319.4375 536.3246)))
(apply 'command (append '("pline") coords '("c")))
(setq currobj (ssadd (entlast) currobj))
(setq coords (list 
(list 319.4375 536.1816) 
(list 245.415 535.9316) 
(list 245.415 535.7546) 
(list 319.4375 536.1046)))
(apply 'command (append '("pline") coords '("c")))
(setq currobj (ssadd (entlast) currobj))
(setq coords (list 
(list 319.4375 535.9616) 
(list 245.415 535.6116) 
(list 245.415 535.4346) 
(list 319.4375 535.8846)))
(apply 'command (append '("pline") coords '("c")))
(setq currobj (ssadd (entlast) currobj))
(setq coords (list 
(list 319.4375 535.7416) 
(list 245.415 535.2916) 
(list 245.415 535.1146) 
(list 319.4375 535.6646)))
(apply 'command (append '("pline") coords '("c")))
(setq currobj (ssadd (entlast) currobj))
(setq coords (list 
(list 319.4375 535.5216) 
(list 245.415 534.9716) 
(list 245.415 534.7946) 
(list 319.4375 535.4446)))
(apply 'command (append '("pline") coords '("c")))
(setq currobj (ssadd (entlast) currobj))
(setq coords (list 
(list 319.4375 535.3016) 
(list 245.415 534.6516) 
(list 245.415 534.4746) 
(list 319.4375 535.2246)))
(apply 'command (append '("pline") coords '("c")))
(setq currobj (ssadd (entlast) currobj))
(command "_layer" "set" "nitride" "")
(command "_layer" "set" "text" "")
(command "_circle" "319.0625,524.0816" "0.075")
(command "_circle" "319.0625,524.3816" "0.075")
(command "_circle" "319.0625,524.6816" "0.075")
(command "_circle" "319.0625,524.9816" "0.075")
(command "_circle" "319.0625,525.2816" "0.075")
(command "_circle" "318.7625,524.0816" "0.075")
(command "_circle" "318.7625,524.3816" "0.075")
(command "_circle" "318.7625,524.6816" "0.075")
(command "_circle" "318.7625,524.9816" "0.075")
(command "_circle" "318.7625,525.2816" "0.075")
(command "_circle" "318.4625,524.0816" "0.075")
(command "_circle" "318.4625,524.3816" "0.075")
(command "_circle" "318.4625,524.6816" "0.075")
(command "_circle" "318.4625,524.9816" "0.075")
(command "_circle" "318.4625,525.2816" "0.075")
(command "_circle" "318.1625,524.0816" "0.075")
(command "_circle" "318.1625,524.3816" "0.075")
(command "_circle" "318.1625,524.6816" "0.075")
(command "_circle" "318.1625,524.9816" "0.075")
(command "_circle" "318.1625,525.2816" "0.075")
(command "_circle" "317.8625,524.0816" "0.075")
(command "_circle" "317.8625,524.3816" "0.075")
(command "_circle" "317.8625,524.6816" "0.075")
(command "_circle" "317.8625,524.9816" "0.075")
(command "_circle" "317.8625,525.2816" "0.075")
(command "_layer" "set" "nitride" "")
(setq coords (list 
(list 320.2625 549.5246) 
(list 320.2625 665.1693) 
(list 319.7375 665.1693) 
(list 319.7375 549.5246)))
(apply 'command (append '("pline") coords '("c")))
(setq currobj (ssadd (entlast) currobj))
(command "_layer" "set" "prebias" "")
(command "_rectangle" "319.7375,549.5246" "320.2625,665.1693")
(setq currobj (ssadd (entlast) currobj))
(command "_layer" "set" "nitride" "")
(setq coords (list 
(list 320.2625 665.1693) 
(list 320.5625 675.1693) 
(list 320.5625 675.1693) 
(list 320.5625 676.1693) 
(list 394.585 675.4193) 
(list 394.585 680.3623) 
(list 320.5625 679.6123) 
(list 320.5625 680.6123) 
(list 320.5625 680.6123) 
(list 320.2625 690.6123) 
(list 319.7375 690.6123) 
(list 319.4375 680.6123) 
(list 319.4375 680.6123) 
(list 319.4375 679.6123) 
(list 245.415 680.3623) 
(list 245.415 675.4193) 
(list 319.4375 676.1693) 
(list 319.4375 675.1693) 
(list 319.4375 675.1693) 
(list 319.7375 665.1693)))
(apply 'command (append '("pline") coords '("c")))
(setq currobj (ssadd (entlast) currobj))
(command "_layer" "set" "prebias" "")
(setq coords (list 
(list 319.4375 665.1693) 
(list 319.4375 676.1693) 
(list 245.415 675.4193) 
(list 245.415 680.3623) 
(list 319.4375 679.6123) 
(list 319.4375 690.6123) 
(list 320.5625 690.6123) 
(list 320.5625 679.6123) 
(list 394.585 680.3623) 
(list 394.585 675.4193) 
(list 320.5625 676.1693) 
(list 320.5625 665.1693)))
(apply 'command (append '("pline") coords '("c")))
(setq currobj (ssadd (entlast) currobj))
(command "_layer" "set" "nitride" "")
(command "_layer" "set" "fda1" "")
(setq coords (list 
(list 320.5625 676.3123) 
(list 394.585 675.5623) 
(list 394.585 675.7393) 
(list 320.5625 676.3893)))
(apply 'command (append '("pline") coords '("c")))
(setq currobj (ssadd (entlast) currobj))
(setq coords (list 
(list 320.5625 676.5323) 
(list 394.585 675.8823) 
(list 394.585 676.0593) 
(list 320.5625 676.6093)))
(apply 'command (append '("pline") coords '("c")))
(setq currobj (ssadd (entlast) currobj))
(setq coords (list 
(list 320.5625 676.7523) 
(list 394.585 676.2023) 
(list 394.585 676.3793) 
(list 320.5625 676.8293)))
(apply 'command (append '("pline") coords '("c")))
(setq currobj (ssadd (entlast) currobj))
(setq coords (list 
(list 320.5625 676.9723) 
(list 394.585 676.5223) 
(list 394.585 676.6993) 
(list 320.5625 677.0493)))
(apply 'command (append '("pline") coords '("c")))
(setq currobj (ssadd (entlast) currobj))
(setq coords (list 
(list 320.5625 677.1923) 
(list 394.585 676.8423) 
(list 394.585 677.0193) 
(list 320.5625 677.2693)))
(apply 'command (append '("pline") coords '("c")))
(setq currobj (ssadd (entlast) currobj))
(setq coords (list 
(list 320.5625 677.4123) 
(list 394.585 677.1623) 
(list 394.585 677.3393) 
(list 320.5625 677.4893)))
(apply 'command (append '("pline") coords '("c")))
(setq currobj (ssadd (entlast) currobj))
(setq coords (list 
(list 320.5625 677.6323) 
(list 394.585 677.4823) 
(list 394.585 677.6593) 
(list 320.5625 677.7093)))
(apply 'command (append '("pline") coords '("c")))
(setq currobj (ssadd (entlast) currobj))
(setq coords (list 
(list 320.5625 677.8523) 
(list 394.585 677.8023) 
(list 394.585 677.9793) 
(list 320.5625 677.9293)))
(apply 'command (append '("pline") coords '("c")))
(setq currobj (ssadd (entlast) currobj))
(setq coords (list 
(list 320.5625 678.0723) 
(list 394.585 678.1223) 
(list 394.585 678.2993) 
(list 320.5625 678.1493)))
(apply 'command (append '("pline") coords '("c")))
(setq currobj (ssadd (entlast) currobj))
(setq coords (list 
(list 320.5625 678.2923) 
(list 394.585 678.4423) 
(list 394.585 678.6193) 
(list 320.5625 678.3693)))
(apply 'command (append '("pline") coords '("c")))
(setq currobj (ssadd (entlast) currobj))
(setq coords (list 
(list 320.5625 678.5123) 
(list 394.585 678.7623) 
(list 394.585 678.9393) 
(list 320.5625 678.5893)))
(apply 'command (append '("pline") coords '("c")))
(setq currobj (ssadd (entlast) currobj))
(setq coords (list 
(list 320.5625 678.7323) 
(list 394.585 679.0823) 
(list 394.585 679.2593) 
(list 320.5625 678.8093)))
(apply 'command (append '("pline") coords '("c")))
(setq currobj (ssadd (entlast) currobj))
(setq coords (list 
(list 320.5625 678.9523) 
(list 394.585 679.4023) 
(list 394.585 679.5793) 
(list 320.5625 679.0293)))
(apply 'command (append '("pline") coords '("c")))
(setq currobj (ssadd (entlast) currobj))
(setq coords (list 
(list 320.5625 679.1723) 
(list 394.585 679.7223) 
(list 394.585 679.8993) 
(list 320.5625 679.2493)))
(apply 'command (append '("pline") coords '("c")))
(setq currobj (ssadd (entlast) currobj))
(setq coords (list 
(list 320.5625 679.3923) 
(list 394.585 680.0423) 
(list 394.585 680.2193) 
(list 320.5625 679.4693)))
(apply 'command (append '("pline") coords '("c")))
(setq currobj (ssadd (entlast) currobj))
(setq coords (list 
(list 319.4375 679.4693) 
(list 245.415 680.2193) 
(list 245.415 680.0423) 
(list 319.4375 679.3923)))
(apply 'command (append '("pline") coords '("c")))
(setq currobj (ssadd (entlast) currobj))
(setq coords (list 
(list 319.4375 679.2493) 
(list 245.415 679.8993) 
(list 245.415 679.7223) 
(list 319.4375 679.1723)))
(apply 'command (append '("pline") coords '("c")))
(setq currobj (ssadd (entlast) currobj))
(setq coords (list 
(list 319.4375 679.0293) 
(list 245.415 679.5793) 
(list 245.415 679.4023) 
(list 319.4375 678.9523)))
(apply 'command (append '("pline") coords '("c")))
(setq currobj (ssadd (entlast) currobj))
(setq coords (list 
(list 319.4375 678.8093) 
(list 245.415 679.2593) 
(list 245.415 679.0823) 
(list 319.4375 678.7323)))
(apply 'command (append '("pline") coords '("c")))
(setq currobj (ssadd (entlast) currobj))
(setq coords (list 
(list 319.4375 678.5893) 
(list 245.415 678.9393) 
(list 245.415 678.7623) 
(list 319.4375 678.5123)))
(apply 'command (append '("pline") coords '("c")))
(setq currobj (ssadd (entlast) currobj))
(setq coords (list 
(list 319.4375 678.3693) 
(list 245.415 678.6193) 
(list 245.415 678.4423) 
(list 319.4375 678.2923)))
(apply 'command (append '("pline") coords '("c")))
(setq currobj (ssadd (entlast) currobj))
(setq coords (list 
(list 319.4375 678.1493) 
(list 245.415 678.2993) 
(list 245.415 678.1223) 
(list 319.4375 678.0723)))
(apply 'command (append '("pline") coords '("c")))
(setq currobj (ssadd (entlast) currobj))
(setq coords (list 
(list 319.4375 677.9293) 
(list 245.415 677.9793) 
(list 245.415 677.8023) 
(list 319.4375 677.8523)))
(apply 'command (append '("pline") coords '("c")))
(setq currobj (ssadd (entlast) currobj))
(setq coords (list 
(list 319.4375 677.7093) 
(list 245.415 677.6593) 
(list 245.415 677.4823) 
(list 319.4375 677.6323)))
(apply 'command (append '("pline") coords '("c")))
(setq currobj (ssadd (entlast) currobj))
(setq coords (list 
(list 319.4375 677.4893) 
(list 245.415 677.3393) 
(list 245.415 677.1623) 
(list 319.4375 677.4123)))
(apply 'command (append '("pline") coords '("c")))
(setq currobj (ssadd (entlast) currobj))
(setq coords (list 
(list 319.4375 677.2693) 
(list 245.415 677.0193) 
(list 245.415 676.8423) 
(list 319.4375 677.1923)))
(apply 'command (append '("pline") coords '("c")))
(setq currobj (ssadd (entlast) currobj))
(setq coords (list 
(list 319.4375 677.0493) 
(list 245.415 676.6993) 
(list 245.415 676.5223) 
(list 319.4375 676.9723)))
(apply 'command (append '("pline") coords '("c")))
(setq currobj (ssadd (entlast) currobj))
(setq coords (list 
(list 319.4375 676.8293) 
(list 245.415 676.3793) 
(list 245.415 676.2023) 
(list 319.4375 676.7523)))
(apply 'command (append '("pline") coords '("c")))
(setq currobj (ssadd (entlast) currobj))
(setq coords (list 
(list 319.4375 676.6093) 
(list 245.415 676.0593) 
(list 245.415 675.8823) 
(list 319.4375 676.5323)))
(apply 'command (append '("pline") coords '("c")))
(setq currobj (ssadd (entlast) currobj))
(setq coords (list 
(list 319.4375 676.3893) 
(list 245.415 675.7393) 
(list 245.415 675.5623) 
(list 319.4375 676.3123)))
(apply 'command (append '("pline") coords '("c")))
(setq currobj (ssadd (entlast) currobj))
(command "_layer" "set" "nitride" "")
(command "_layer" "set" "text" "")
(command "_circle" "319.0625,665.1693" "0.075")
(command "_circle" "319.0625,665.4693" "0.075")
(command "_circle" "319.0625,665.7693" "0.075")
(command "_circle" "319.0625,666.0693" "0.075")
(command "_circle" "319.0625,666.3693" "0.075")
(command "_circle" "318.7625,665.1693" "0.075")
(command "_circle" "318.7625,665.4693" "0.075")
(command "_circle" "318.7625,665.7693" "0.075")
(command "_circle" "318.7625,666.0693" "0.075")
(command "_circle" "318.7625,666.3693" "0.075")
(command "_circle" "318.4625,665.1693" "0.075")
(command "_circle" "318.4625,665.4693" "0.075")
(command "_circle" "318.4625,665.7693" "0.075")
(command "_circle" "318.4625,666.0693" "0.075")
(command "_circle" "318.4625,666.3693" "0.075")
(command "_circle" "318.1625,665.1693" "0.075")
(command "_circle" "318.1625,665.4693" "0.075")
(command "_circle" "318.1625,665.7693" "0.075")
(command "_circle" "318.1625,666.0693" "0.075")
(command "_circle" "318.1625,666.3693" "0.075")
(command "_circle" "317.8625,665.1693" "0.075")
(command "_circle" "317.8625,665.4693" "0.075")
(command "_circle" "317.8625,665.7693" "0.075")
(command "_circle" "317.8625,666.0693" "0.075")
(command "_circle" "317.8625,666.3693" "0.075")
(command "_layer" "set" "nitride" "")
(setq coords (list 
(list 320.2625 690.6123) 
(list 320.2625 806.257) 
(list 319.7375 806.257) 
(list 319.7375 690.6123)))
(apply 'command (append '("pline") coords '("c")))
(setq currobj (ssadd (entlast) currobj))
(command "_layer" "set" "prebias" "")
(command "_rectangle" "319.7375,690.6123" "320.2625,806.257")
(setq currobj (ssadd (entlast) currobj))
(command "_layer" "set" "nitride" "")
(setq coords (list 
(list 320.2625 806.257) 
(list 320.5625 816.257) 
(list 320.5625 816.257) 
(list 320.5625 817.257) 
(list 394.585 816.507) 
(list 394.585 821.45) 
(list 320.5625 820.7) 
(list 320.5625 821.7) 
(list 320.5625 821.7) 
(list 320.2625 831.7) 
(list 319.7375 831.7) 
(list 319.4375 821.7) 
(list 319.4375 821.7) 
(list 319.4375 820.7) 
(list 245.415 821.45) 
(list 245.415 816.507) 
(list 319.4375 817.257) 
(list 319.4375 816.257) 
(list 319.4375 816.257) 
(list 319.7375 806.257)))
(apply 'command (append '("pline") coords '("c")))
(setq currobj (ssadd (entlast) currobj))
(command "_layer" "set" "prebias" "")
(setq coords (list 
(list 319.4375 806.257) 
(list 319.4375 817.257) 
(list 245.415 816.507) 
(list 245.415 821.45) 
(list 319.4375 820.7) 
(list 319.4375 831.7) 
(list 320.5625 831.7) 
(list 320.5625 820.7) 
(list 394.585 821.45) 
(list 394.585 816.507) 
(list 320.5625 817.257) 
(list 320.5625 806.257)))
(apply 'command (append '("pline") coords '("c")))
(setq currobj (ssadd (entlast) currobj))
(command "_layer" "set" "nitride" "")
(command "_layer" "set" "fda1" "")
(setq coords (list 
(list 320.5625 817.4) 
(list 394.585 816.65) 
(list 394.585 816.827) 
(list 320.5625 817.477)))
(apply 'command (append '("pline") coords '("c")))
(setq currobj (ssadd (entlast) currobj))
(setq coords (list 
(list 320.5625 817.62) 
(list 394.585 816.97) 
(list 394.585 817.147) 
(list 320.5625 817.697)))
(apply 'command (append '("pline") coords '("c")))
(setq currobj (ssadd (entlast) currobj))
(setq coords (list 
(list 320.5625 817.84) 
(list 394.585 817.29) 
(list 394.585 817.467) 
(list 320.5625 817.917)))
(apply 'command (append '("pline") coords '("c")))
(setq currobj (ssadd (entlast) currobj))
(setq coords (list 
(list 320.5625 818.06) 
(list 394.585 817.61) 
(list 394.585 817.787) 
(list 320.5625 818.137)))
(apply 'command (append '("pline") coords '("c")))
(setq currobj (ssadd (entlast) currobj))
(setq coords (list 
(list 320.5625 818.28) 
(list 394.585 817.93) 
(list 394.585 818.107) 
(list 320.5625 818.357)))
(apply 'command (append '("pline") coords '("c")))
(setq currobj (ssadd (entlast) currobj))
(setq coords (list 
(list 320.5625 818.5) 
(list 394.585 818.25) 
(list 394.585 818.427) 
(list 320.5625 818.577)))
(apply 'command (append '("pline") coords '("c")))
(setq currobj (ssadd (entlast) currobj))
(setq coords (list 
(list 320.5625 818.72) 
(list 394.585 818.57) 
(list 394.585 818.747) 
(list 320.5625 818.797)))
(apply 'command (append '("pline") coords '("c")))
(setq currobj (ssadd (entlast) currobj))
(setq coords (list 
(list 320.5625 818.94) 
(list 394.585 818.89) 
(list 394.585 819.067) 
(list 320.5625 819.017)))
(apply 'command (append '("pline") coords '("c")))
(setq currobj (ssadd (entlast) currobj))
(setq coords (list 
(list 320.5625 819.16) 
(list 394.585 819.21) 
(list 394.585 819.387) 
(list 320.5625 819.237)))
(apply 'command (append '("pline") coords '("c")))
(setq currobj (ssadd (entlast) currobj))
(setq coords (list 
(list 320.5625 819.38) 
(list 394.585 819.53) 
(list 394.585 819.707) 
(list 320.5625 819.457)))
(apply 'command (append '("pline") coords '("c")))
(setq currobj (ssadd (entlast) currobj))
(setq coords (list 
(list 320.5625 819.6) 
(list 394.585 819.85) 
(list 394.585 820.027) 
(list 320.5625 819.677)))
(apply 'command (append '("pline") coords '("c")))
(setq currobj (ssadd (entlast) currobj))
(setq coords (list 
(list 320.5625 819.82) 
(list 394.585 820.17) 
(list 394.585 820.347) 
(list 320.5625 819.897)))
(apply 'command (append '("pline") coords '("c")))
(setq currobj (ssadd (entlast) currobj))
(setq coords (list 
(list 320.5625 820.04) 
(list 394.585 820.49) 
(list 394.585 820.667) 
(list 320.5625 820.117)))
(apply 'command (append '("pline") coords '("c")))
(setq currobj (ssadd (entlast) currobj))
(setq coords (list 
(list 320.5625 820.26) 
(list 394.585 820.81) 
(list 394.585 820.987) 
(list 320.5625 820.337)))
(apply 'command (append '("pline") coords '("c")))
(setq currobj (ssadd (entlast) currobj))
(setq coords (list 
(list 320.5625 820.48) 
(list 394.585 821.13) 
(list 394.585 821.307) 
(list 320.5625 820.557)))
(apply 'command (append '("pline") coords '("c")))
(setq currobj (ssadd (entlast) currobj))
(setq coords (list 
(list 319.4375 820.557) 
(list 245.415 821.307) 
(list 245.415 821.13) 
(list 319.4375 820.48)))
(apply 'command (append '("pline") coords '("c")))
(setq currobj (ssadd (entlast) currobj))
(setq coords (list 
(list 319.4375 820.337) 
(list 245.415 820.987) 
(list 245.415 820.81) 
(list 319.4375 820.26)))
(apply 'command (append '("pline") coords '("c")))
(setq currobj (ssadd (entlast) currobj))
(setq coords (list 
(list 319.4375 820.117) 
(list 245.415 820.667) 
(list 245.415 820.49) 
(list 319.4375 820.04)))
(apply 'command (append '("pline") coords '("c")))
(setq currobj (ssadd (entlast) currobj))
(setq coords (list 
(list 319.4375 819.897) 
(list 245.415 820.347) 
(list 245.415 820.17) 
(list 319.4375 819.82)))
(apply 'command (append '("pline") coords '("c")))
(setq currobj (ssadd (entlast) currobj))
(setq coords (list 
(list 319.4375 819.677) 
(list 245.415 820.027) 
(list 245.415 819.85) 
(list 319.4375 819.6)))
(apply 'command (append '("pline") coords '("c")))
(setq currobj (ssadd (entlast) currobj))
(setq coords (list 
(list 319.4375 819.457) 
(list 245.415 819.707) 
(list 245.415 819.53) 
(list 319.4375 819.38)))
(apply 'command (append '("pline") coords '("c")))
(setq currobj (ssadd (entlast) currobj))
(setq coords (list 
(list 319.4375 819.237) 
(list 245.415 819.387) 
(list 245.415 819.21) 
(list 319.4375 819.16)))
(apply 'command (append '("pline") coords '("c")))
(setq currobj (ssadd (entlast) currobj))
(setq coords (list 
(list 319.4375 819.017) 
(list 245.415 819.067) 
(list 245.415 818.89) 
(list 319.4375 818.94)))
(apply 'command (append '("pline") coords '("c")))
(setq currobj (ssadd (entlast) currobj))
(setq coords (list 
(list 319.4375 818.797) 
(list 245.415 818.747) 
(list 245.415 818.57) 
(list 319.4375 818.72)))
(apply 'command (append '("pline") coords '("c")))
(setq currobj (ssadd (entlast) currobj))
(setq coords (list 
(list 319.4375 818.577) 
(list 245.415 818.427) 
(list 245.415 818.25) 
(list 319.4375 818.5)))
(apply 'command (append '("pline") coords '("c")))
(setq currobj (ssadd (entlast) currobj))
(setq coords (list 
(list 319.4375 818.357) 
(list 245.415 818.107) 
(list 245.415 817.93) 
(list 319.4375 818.28)))
(apply 'command (append '("pline") coords '("c")))
(setq currobj (ssadd (entlast) currobj))
(setq coords (list 
(list 319.4375 818.137) 
(list 245.415 817.787) 
(list 245.415 817.61) 
(list 319.4375 818.06)))
(apply 'command (append '("pline") coords '("c")))
(setq currobj (ssadd (entlast) currobj))
(setq coords (list 
(list 319.4375 817.917) 
(list 245.415 817.467) 
(list 245.415 817.29) 
(list 319.4375 817.84)))
(apply 'command (append '("pline") coords '("c")))
(setq currobj (ssadd (entlast) currobj))
(setq coords (list 
(list 319.4375 817.697) 
(list 245.415 817.147) 
(list 245.415 816.97) 
(list 319.4375 817.62)))
(apply 'command (append '("pline") coords '("c")))
(setq currobj (ssadd (entlast) currobj))
(setq coords (list 
(list 319.4375 817.477) 
(list 245.415 816.827) 
(list 245.415 816.65) 
(list 319.4375 817.4)))
(apply 'command (append '("pline") coords '("c")))
(setq currobj (ssadd (entlast) currobj))
(command "_layer" "set" "nitride" "")
(command "_layer" "set" "text" "")
(command "_circle" "319.0625,806.257" "0.075")
(command "_circle" "319.0625,806.557" "0.075")
(command "_circle" "319.0625,806.857" "0.075")
(command "_circle" "319.0625,807.157" "0.075")
(command "_circle" "319.0625,807.457" "0.075")
(command "_circle" "318.7625,806.257" "0.075")
(command "_circle" "318.7625,806.557" "0.075")
(command "_circle" "318.7625,806.857" "0.075")
(command "_circle" "318.7625,807.157" "0.075")
(command "_circle" "318.7625,807.457" "0.075")
(command "_circle" "318.4625,806.257" "0.075")
(command "_circle" "318.4625,806.557" "0.075")
(command "_circle" "318.4625,806.857" "0.075")
(command "_circle" "318.4625,807.157" "0.075")
(command "_circle" "318.4625,807.457" "0.075")
(command "_circle" "318.1625,806.257" "0.075")
(command "_circle" "318.1625,806.557" "0.075")
(command "_circle" "318.1625,806.857" "0.075")
(command "_circle" "318.1625,807.157" "0.075")
(command "_circle" "318.1625,807.457" "0.075")
(command "_circle" "317.8625,806.257" "0.075")
(command "_circle" "317.8625,806.557" "0.075")
(command "_circle" "317.8625,806.857" "0.075")
(command "_circle" "317.8625,807.157" "0.075")
(command "_circle" "317.8625,807.457" "0.075")
(command "_layer" "set" "nitride" "")
(setq coords (list 
(list 320.2625 831.7) 
(list 320.2625 836.7) 
(list 319.7375 836.7) 
(list 319.7375 831.7)))
(apply 'command (append '("pline") coords '("c")))
(setq currobj (ssadd (entlast) currobj))
(command "_layer" "set" "prebias" "")
(command "_rectangle" "319.7375,831.7" "320.2625,836.7")
(setq currobj (ssadd (entlast) currobj))
(command "_layer" "set" "nitride" "")
(setq cooledsinglenanobeam1 currobj)
(setq currobj nil)
(setq currobj (ssadd))
; DRAWING PHOTONIC CRYSTAL
(command "_layer" "set" "negYjunc" "")
(setq coords (list 
(list 320.125 866.7) 
(list 320 851.7) 
(list 320 866.7)))
(apply 'command (append '("pline") coords '("c")))
(setq currobj (ssadd (entlast) currobj))
(setq coords (list 
(list 320.2625 836.7) 
(list 320.405 866.7) 
(list 321.082 866.7) 
(list 321.082 836.7)))
(apply 'command (append '("pline") coords '("c")))
(setq currobj (ssadd (entlast) currobj))
(setq coords (list 
(list 319.875 866.7) 
(list 320 851.7) 
(list 320 866.7)))
(apply 'command (append '("pline") coords '("c")))
(setq currobj (ssadd (entlast) currobj))
(setq coords (list 
(list 319.7375 836.7) 
(list 319.595 866.7) 
(list 318.918 866.7) 
(list 318.918 836.7)))
(apply 'command (append '("pline") coords '("c")))
(setq currobj (ssadd (entlast) currobj))
(command "_layer" "set" "nitride" "")
(setq yjunction1 currobj)
(setq currobj nil)
(setq currobj (ssadd))
(setq tap1 nil)
(setq tap1 (ssadd))
(command "_layer" "set" "phc" "")
(setq coords (list 
(list 320 866.7) 
(list 320.125 866.7) 
(list 320.125 866.7103) 
(list 320.125 866.7206) 
(list 320.125 866.7308) 
(list 320.125 866.7411) 
(list 320.125 866.7514) 
(list 320.125 866.7617) 
(list 320.125 866.7719) 
(list 320.125 866.7822) 
(list 320.125 866.7925) 
(list 320.125 866.8028) 
(list 320.125 866.8131) 
(list 320.125 866.8233) 
(list 320.125 866.8336) 
(list 320.125 866.8439) 
(list 320.125 866.8542) 
(list 320.125 866.8644) 
(list 320.125 866.8747) 
(list 320.125 866.885) 
(list 320.125 866.8953) 
(list 320.125 866.9056) 
(list 320.125 866.9158) 
(list 320.125 866.9261) 
(list 320.125 866.9364) 
(list 320.125 866.9467) 
(list 320.125 866.9569) 
(list 320.125 866.9672) 
(list 320.125 866.9775) 
(list 320.125 866.9878) 
(list 320.125 866.9981) 
(list 320.125 867.0083) 
(list 320.125 867.0186) 
(list 320.125 867.0289) 
(list 320.125 867.0392) 
(list 320.125 867.0494) 
(list 320.125 867.0597) 
(list 320.125 867.07) 
(list 320 867.07)))
(apply 'command (append '("pline") coords '("c")))
(setq tap1 (ssadd (entlast) tap1))
(command "_mirror" (entlast) "" "320,900" "320,901" "No")
(setq tap1 (ssadd (entlast) tap1))
(setq coords (list 
(list 320.4141 866.7) 
(list 320.405 866.7) 
(list 320.4052 866.7103) 
(list 320.4055 866.7206) 
(list 320.4057 866.7308) 
(list 320.4058 866.7411) 
(list 320.4058 866.7514) 
(list 320.4058 866.7617) 
(list 320.4057 866.7719) 
(list 320.4055 866.7822) 
(list 320.4051 866.7925) 
(list 320.4048 866.8028) 
(list 320.4043 866.8131) 
(list 320.4038 866.8233) 
(list 320.4033 866.8336) 
(list 320.4027 866.8439) 
(list 320.4022 866.8542) 
(list 320.4017 866.8644) 
(list 320.4013 866.8747) 
(list 320.4011 866.885) 
(list 320.4009 866.8953) 
(list 320.4009 866.9056) 
(list 320.4011 866.9158) 
(list 320.4014 866.9261) 
(list 320.4019 866.9364) 
(list 320.4026 866.9467) 
(list 320.4034 866.9569) 
(list 320.4044 866.9672) 
(list 320.4054 866.9775) 
(list 320.4066 866.9878) 
(list 320.4078 866.9981) 
(list 320.409 867.0083) 
(list 320.4102 867.0186) 
(list 320.4113 867.0289) 
(list 320.4123 867.0392) 
(list 320.4131 867.0494) 
(list 320.4137 867.0597) 
(list 320.4141 867.07) 
(list 320.4141 867.07)))
(apply 'command (append '("pline") coords '("c")))
(setq tap1 (ssadd (entlast) tap1))
(command "_mirror" (entlast) "" "320,900" "320,901" "No")
(setq tap1 (ssadd (entlast) tap1))
(setq coords (list 
(list 321.082 866.7) 
(list 320.4141 866.7) 
(list 320.4141 866.7103) 
(list 320.4141 866.7206) 
(list 320.4141 866.7308) 
(list 320.4141 866.7411) 
(list 320.4141 866.7514) 
(list 320.4141 866.7617) 
(list 320.4141 866.7719) 
(list 320.4141 866.7822) 
(list 320.4141 866.7925) 
(list 320.4141 866.8028) 
(list 320.4141 866.8131) 
(list 320.4141 866.8233) 
(list 320.4141 866.8336) 
(list 320.4141 866.8439) 
(list 320.4141 866.8542) 
(list 320.4141 866.8644) 
(list 320.4141 866.8747) 
(list 320.4141 866.885) 
(list 320.4141 866.8953) 
(list 320.4141 866.9056) 
(list 320.4141 866.9158) 
(list 320.4141 866.9261) 
(list 320.4141 866.9364) 
(list 320.4141 866.9467) 
(list 320.4141 866.9569) 
(list 320.4141 866.9672) 
(list 320.4141 866.9775) 
(list 320.4141 866.9878) 
(list 320.4141 866.9981) 
(list 320.4141 867.0083) 
(list 320.4141 867.0186) 
(list 320.4141 867.0289) 
(list 320.4141 867.0392) 
(list 320.4141 867.0494) 
(list 320.4141 867.0597) 
(list 320.4141 867.07) 
(list 321.082 867.07)))
(apply 'command (append '("pline") coords '("c")))
(setq tap1 (ssadd (entlast) tap1))
(command "_mirror" (entlast) "" "320,900" "320,901" "No")
(setq tap1 (ssadd (entlast) tap1))
(setq coords (list 
(list 320 867.07) 
(list 320.125 867.07) 
(list 320.125 867.0803) 
(list 320.125 867.0906) 
(list 320.125 867.1008) 
(list 320.125 867.1111) 
(list 320.125 867.1214) 
(list 320.125 867.1317) 
(list 320.125 867.1419) 
(list 320.125 867.1522) 
(list 320.125 867.1625) 
(list 320.125 867.1728) 
(list 320.125 867.1831) 
(list 320.125 867.1933) 
(list 320.125 867.2036) 
(list 320.125 867.2139) 
(list 320.125 867.2242) 
(list 320.125 867.2344) 
(list 320.125 867.2447) 
(list 320.125 867.255) 
(list 320.125 867.2653) 
(list 320.125 867.2756) 
(list 320.125 867.2858) 
(list 320.125 867.2961) 
(list 320.125 867.3064) 
(list 320.125 867.3167) 
(list 320.125 867.3269) 
(list 320.125 867.3372) 
(list 320.125 867.3475) 
(list 320.125 867.3578) 
(list 320.125 867.3681) 
(list 320.125 867.3783) 
(list 320.125 867.3886) 
(list 320.125 867.3989) 
(list 320.125 867.4092) 
(list 320.125 867.4194) 
(list 320.125 867.4297) 
(list 320.125 867.44) 
(list 320 867.44)))
(apply 'command (append '("pline") coords '("c")))
(setq tap1 (ssadd (entlast) tap1))
(command "_mirror" (entlast) "" "320,900" "320,901" "No")
(setq tap1 (ssadd (entlast) tap1))
(setq coords (list 
(list 320.4231 867.07) 
(list 320.4141 867.07) 
(list 320.4142 867.0803) 
(list 320.414 867.0906) 
(list 320.4136 867.1008) 
(list 320.4129 867.1111) 
(list 320.4119 867.1214) 
(list 320.4106 867.1317) 
(list 320.4092 867.1419) 
(list 320.4075 867.1522) 
(list 320.4058 867.1625) 
(list 320.4039 867.1728) 
(list 320.402 867.1831) 
(list 320.4002 867.1933) 
(list 320.3984 867.2036) 
(list 320.3968 867.2139) 
(list 320.3955 867.2242) 
(list 320.3944 867.2344) 
(list 320.3936 867.2447) 
(list 320.3932 867.255) 
(list 320.3932 867.2653) 
(list 320.3936 867.2756) 
(list 320.3943 867.2858) 
(list 320.3955 867.2961) 
(list 320.3971 867.3064) 
(list 320.3989 867.3167) 
(list 320.4011 867.3269) 
(list 320.4035 867.3372) 
(list 320.406 867.3475) 
(list 320.4087 867.3578) 
(list 320.4113 867.3681) 
(list 320.4139 867.3783) 
(list 320.4162 867.3886) 
(list 320.4184 867.3989) 
(list 320.4202 867.4092) 
(list 320.4216 867.4194) 
(list 320.4226 867.4297) 
(list 320.4231 867.44) 
(list 320.4231 867.44)))
(apply 'command (append '("pline") coords '("c")))
(setq tap1 (ssadd (entlast) tap1))
(command "_mirror" (entlast) "" "320,900" "320,901" "No")
(setq tap1 (ssadd (entlast) tap1))
(setq coords (list 
(list 321.082 867.07) 
(list 320.4231 867.07) 
(list 320.4231 867.0803) 
(list 320.4231 867.0906) 
(list 320.4231 867.1008) 
(list 320.4231 867.1111) 
(list 320.4231 867.1214) 
(list 320.4231 867.1317) 
(list 320.4231 867.1419) 
(list 320.4231 867.1522) 
(list 320.4231 867.1625) 
(list 320.4231 867.1728) 
(list 320.4231 867.1831) 
(list 320.4231 867.1933) 
(list 320.4231 867.2036) 
(list 320.4231 867.2139) 
(list 320.4231 867.2242) 
(list 320.4231 867.2344) 
(list 320.4231 867.2447) 
(list 320.4231 867.255) 
(list 320.4231 867.2653) 
(list 320.4231 867.2756) 
(list 320.4231 867.2858) 
(list 320.4231 867.2961) 
(list 320.4231 867.3064) 
(list 320.4231 867.3167) 
(list 320.4231 867.3269) 
(list 320.4231 867.3372) 
(list 320.4231 867.3475) 
(list 320.4231 867.3578) 
(list 320.4231 867.3681) 
(list 320.4231 867.3783) 
(list 320.4231 867.3886) 
(list 320.4231 867.3989) 
(list 320.4231 867.4092) 
(list 320.4231 867.4194) 
(list 320.4231 867.4297) 
(list 320.4231 867.44) 
(list 321.082 867.44)))
(apply 'command (append '("pline") coords '("c")))
(setq tap1 (ssadd (entlast) tap1))
(command "_mirror" (entlast) "" "320,900" "320,901" "No")
(setq tap1 (ssadd (entlast) tap1))
(setq coords (list 
(list 320 867.44) 
(list 320.125 867.44) 
(list 320.125 867.4503) 
(list 320.125 867.4606) 
(list 320.125 867.4708) 
(list 320.125 867.4811) 
(list 320.125 867.4914) 
(list 320.125 867.5017) 
(list 320.125 867.5119) 
(list 320.125 867.5222) 
(list 320.125 867.5325) 
(list 320.125 867.5428) 
(list 320.125 867.5531) 
(list 320.125 867.5633) 
(list 320.125 867.5736) 
(list 320.125 867.5839) 
(list 320.125 867.5942) 
(list 320.125 867.6044) 
(list 320.125 867.6147) 
(list 320.125 867.625) 
(list 320.125 867.6353) 
(list 320.125 867.6456) 
(list 320.125 867.6558) 
(list 320.125 867.6661) 
(list 320.125 867.6764) 
(list 320.125 867.6867) 
(list 320.125 867.6969) 
(list 320.125 867.7072) 
(list 320.125 867.7175) 
(list 320.125 867.7278) 
(list 320.125 867.7381) 
(list 320.125 867.7483) 
(list 320.125 867.7586) 
(list 320.125 867.7689) 
(list 320.125 867.7792) 
(list 320.125 867.7894) 
(list 320.125 867.7997) 
(list 320.125 867.81) 
(list 320 867.81)))
(apply 'command (append '("pline") coords '("c")))
(setq tap1 (ssadd (entlast) tap1))
(command "_mirror" (entlast) "" "320,900" "320,901" "No")
(setq tap1 (ssadd (entlast) tap1))
(setq coords (list 
(list 320.4322 867.44) 
(list 320.4231 867.44) 
(list 320.4231 867.4503) 
(list 320.4226 867.4606) 
(list 320.4215 867.4708) 
(list 320.42 867.4811) 
(list 320.4179 867.4914) 
(list 320.4155 867.5017) 
(list 320.4127 867.5119) 
(list 320.4096 867.5222) 
(list 320.4063 867.5325) 
(list 320.403 867.5428) 
(list 320.3997 867.5531) 
(list 320.3965 867.5633) 
(list 320.3936 867.5736) 
(list 320.3909 867.5839) 
(list 320.3887 867.5942) 
(list 320.387 867.6044) 
(list 320.3859 867.6147) 
(list 320.3853 867.625) 
(list 320.3854 867.6353) 
(list 320.3862 867.6456) 
(list 320.3876 867.6558) 
(list 320.3896 867.6661) 
(list 320.3922 867.6764) 
(list 320.3953 867.6867) 
(list 320.3988 867.6969) 
(list 320.4026 867.7072) 
(list 320.4067 867.7175) 
(list 320.4108 867.7278) 
(list 320.4148 867.7381) 
(list 320.4187 867.7483) 
(list 320.4223 867.7586) 
(list 320.4255 867.7689) 
(list 320.4281 867.7792) 
(list 320.4302 867.7894) 
(list 320.4316 867.7997) 
(list 320.4322 867.81) 
(list 320.4322 867.81)))
(apply 'command (append '("pline") coords '("c")))
(setq tap1 (ssadd (entlast) tap1))
(command "_mirror" (entlast) "" "320,900" "320,901" "No")
(setq tap1 (ssadd (entlast) tap1))
(setq coords (list 
(list 321.082 867.44) 
(list 320.4322 867.44) 
(list 320.4322 867.4503) 
(list 320.4322 867.4606) 
(list 320.4322 867.4708) 
(list 320.4322 867.4811) 
(list 320.4322 867.4914) 
(list 320.4322 867.5017) 
(list 320.4322 867.5119) 
(list 320.4322 867.5222) 
(list 320.4322 867.5325) 
(list 320.4322 867.5428) 
(list 320.4322 867.5531) 
(list 320.4322 867.5633) 
(list 320.4322 867.5736) 
(list 320.4322 867.5839) 
(list 320.4322 867.5942) 
(list 320.4322 867.6044) 
(list 320.4322 867.6147) 
(list 320.4322 867.625) 
(list 320.4322 867.6353) 
(list 320.4322 867.6456) 
(list 320.4322 867.6558) 
(list 320.4322 867.6661) 
(list 320.4322 867.6764) 
(list 320.4322 867.6867) 
(list 320.4322 867.6969) 
(list 320.4322 867.7072) 
(list 320.4322 867.7175) 
(list 320.4322 867.7278) 
(list 320.4322 867.7381) 
(list 320.4322 867.7483) 
(list 320.4322 867.7586) 
(list 320.4322 867.7689) 
(list 320.4322 867.7792) 
(list 320.4322 867.7894) 
(list 320.4322 867.7997) 
(list 320.4322 867.81) 
(list 321.082 867.81)))
(apply 'command (append '("pline") coords '("c")))
(setq tap1 (ssadd (entlast) tap1))
(command "_mirror" (entlast) "" "320,900" "320,901" "No")
(setq tap1 (ssadd (entlast) tap1))
(setq coords (list 
(list 320 867.81) 
(list 320.125 867.81) 
(list 320.125 867.8203) 
(list 320.125 867.8306) 
(list 320.125 867.8408) 
(list 320.125 867.8511) 
(list 320.125 867.8614) 
(list 320.125 867.8717) 
(list 320.125 867.8819) 
(list 320.125 867.8922) 
(list 320.125 867.9025) 
(list 320.125 867.9128) 
(list 320.125 867.9231) 
(list 320.125 867.9333) 
(list 320.125 867.9436) 
(list 320.125 867.9539) 
(list 320.125 867.9642) 
(list 320.125 867.9744) 
(list 320.125 867.9847) 
(list 320.125 867.995) 
(list 320.125 868.0053) 
(list 320.125 868.0156) 
(list 320.125 868.0258) 
(list 320.125 868.0361) 
(list 320.125 868.0464) 
(list 320.125 868.0567) 
(list 320.125 868.0669) 
(list 320.125 868.0772) 
(list 320.125 868.0875) 
(list 320.125 868.0978) 
(list 320.125 868.1081) 
(list 320.125 868.1183) 
(list 320.125 868.1286) 
(list 320.125 868.1389) 
(list 320.125 868.1492) 
(list 320.125 868.1594) 
(list 320.125 868.1697) 
(list 320.125 868.18) 
(list 320 868.18)))
(apply 'command (append '("pline") coords '("c")))
(setq tap1 (ssadd (entlast) tap1))
(command "_mirror" (entlast) "" "320,900" "320,901" "No")
(setq tap1 (ssadd (entlast) tap1))
(setq coords (list 
(list 320.4413 867.81) 
(list 320.4322 867.81) 
(list 320.4321 867.8203) 
(list 320.4311 867.8306) 
(list 320.4295 867.8408) 
(list 320.427 867.8511) 
(list 320.424 867.8614) 
(list 320.4203 867.8717) 
(list 320.4162 867.8819) 
(list 320.4117 867.8922) 
(list 320.4069 867.9025) 
(list 320.4021 867.9128) 
(list 320.3974 867.9231) 
(list 320.3929 867.9333) 
(list 320.3887 867.9436) 
(list 320.3851 867.9539) 
(list 320.382 867.9642) 
(list 320.3797 867.9744) 
(list 320.3781 867.9847) 
(list 320.3775 867.995) 
(list 320.3777 868.0053) 
(list 320.3788 868.0156) 
(list 320.3809 868.0258) 
(list 320.3837 868.0361) 
(list 320.3874 868.0464) 
(list 320.3917 868.0567) 
(list 320.3965 868.0669) 
(list 320.4018 868.0772) 
(list 320.4072 868.0875) 
(list 320.4128 868.0978) 
(list 320.4183 868.1081) 
(list 320.4235 868.1183) 
(list 320.4283 868.1286) 
(list 320.4326 868.1389) 
(list 320.4361 868.1492) 
(list 320.4387 868.1594) 
(list 320.4405 868.1697) 
(list 320.4413 868.18) 
(list 320.4413 868.18)))
(apply 'command (append '("pline") coords '("c")))
(setq tap1 (ssadd (entlast) tap1))
(command "_mirror" (entlast) "" "320,900" "320,901" "No")
(setq tap1 (ssadd (entlast) tap1))
(setq coords (list 
(list 321.082 867.81) 
(list 320.4413 867.81) 
(list 320.4413 867.8203) 
(list 320.4413 867.8306) 
(list 320.4413 867.8408) 
(list 320.4413 867.8511) 
(list 320.4413 867.8614) 
(list 320.4413 867.8717) 
(list 320.4413 867.8819) 
(list 320.4413 867.8922) 
(list 320.4413 867.9025) 
(list 320.4413 867.9128) 
(list 320.4413 867.9231) 
(list 320.4413 867.9333) 
(list 320.4413 867.9436) 
(list 320.4413 867.9539) 
(list 320.4413 867.9642) 
(list 320.4413 867.9744) 
(list 320.4413 867.9847) 
(list 320.4413 867.995) 
(list 320.4413 868.0053) 
(list 320.4413 868.0156) 
(list 320.4413 868.0258) 
(list 320.4413 868.0361) 
(list 320.4413 868.0464) 
(list 320.4413 868.0567) 
(list 320.4413 868.0669) 
(list 320.4413 868.0772) 
(list 320.4413 868.0875) 
(list 320.4413 868.0978) 
(list 320.4413 868.1081) 
(list 320.4413 868.1183) 
(list 320.4413 868.1286) 
(list 320.4413 868.1389) 
(list 320.4413 868.1492) 
(list 320.4413 868.1594) 
(list 320.4413 868.1697) 
(list 320.4413 868.18) 
(list 321.082 868.18)))
(apply 'command (append '("pline") coords '("c")))
(setq tap1 (ssadd (entlast) tap1))
(command "_mirror" (entlast) "" "320,900" "320,901" "No")
(setq tap1 (ssadd (entlast) tap1))
(setq coords (list 
(list 320 868.18) 
(list 320.125 868.18) 
(list 320.125 868.1903) 
(list 320.125 868.2006) 
(list 320.125 868.2108) 
(list 320.125 868.2211) 
(list 320.125 868.2314) 
(list 320.125 868.2417) 
(list 320.125 868.2519) 
(list 320.125 868.2622) 
(list 320.125 868.2725) 
(list 320.125 868.2828) 
(list 320.125 868.2931) 
(list 320.125 868.3033) 
(list 320.125 868.3136) 
(list 320.125 868.3239) 
(list 320.125 868.3342) 
(list 320.125 868.3444) 
(list 320.125 868.3547) 
(list 320.125 868.365) 
(list 320.125 868.3753) 
(list 320.125 868.3856) 
(list 320.125 868.3958) 
(list 320.125 868.4061) 
(list 320.125 868.4164) 
(list 320.125 868.4267) 
(list 320.125 868.4369) 
(list 320.125 868.4472) 
(list 320.125 868.4575) 
(list 320.125 868.4678) 
(list 320.125 868.4781) 
(list 320.125 868.4883) 
(list 320.125 868.4986) 
(list 320.125 868.5089) 
(list 320.125 868.5192) 
(list 320.125 868.5294) 
(list 320.125 868.5397) 
(list 320.125 868.55) 
(list 320 868.55)))
(apply 'command (append '("pline") coords '("c")))
(setq tap1 (ssadd (entlast) tap1))
(command "_mirror" (entlast) "" "320,900" "320,901" "No")
(setq tap1 (ssadd (entlast) tap1))
(setq coords (list 
(list 320.4503 868.18) 
(list 320.4413 868.18) 
(list 320.441 868.1903) 
(list 320.4397 868.2006) 
(list 320.4374 868.2108) 
(list 320.4341 868.2211) 
(list 320.43 868.2314) 
(list 320.4251 868.2417) 
(list 320.4197 868.2519) 
(list 320.4137 868.2622) 
(list 320.4076 868.2725) 
(list 320.4013 868.2828) 
(list 320.3951 868.2931) 
(list 320.3893 868.3033) 
(list 320.3839 868.3136) 
(list 320.3792 868.3239) 
(list 320.3753 868.3342) 
(list 320.3723 868.3444) 
(list 320.3704 868.3547) 
(list 320.3696 868.365) 
(list 320.37 868.3753) 
(list 320.3715 868.3856) 
(list 320.3741 868.3958) 
(list 320.3779 868.4061) 
(list 320.3825 868.4164) 
(list 320.388 868.4267) 
(list 320.3942 868.4369) 
(list 320.4009 868.4472) 
(list 320.4078 868.4575) 
(list 320.4149 868.4678) 
(list 320.4218 868.4781) 
(list 320.4284 868.4883) 
(list 320.4344 868.4986) 
(list 320.4396 868.5089) 
(list 320.444 868.5192) 
(list 320.4473 868.5294) 
(list 320.4494 868.5397) 
(list 320.4503 868.55) 
(list 320.4503 868.55)))
(apply 'command (append '("pline") coords '("c")))
(setq tap1 (ssadd (entlast) tap1))
(command "_mirror" (entlast) "" "320,900" "320,901" "No")
(setq tap1 (ssadd (entlast) tap1))
(setq coords (list 
(list 321.082 868.18) 
(list 320.4503 868.18) 
(list 320.4503 868.1903) 
(list 320.4503 868.2006) 
(list 320.4503 868.2108) 
(list 320.4503 868.2211) 
(list 320.4503 868.2314) 
(list 320.4503 868.2417) 
(list 320.4503 868.2519) 
(list 320.4503 868.2622) 
(list 320.4503 868.2725) 
(list 320.4503 868.2828) 
(list 320.4503 868.2931) 
(list 320.4503 868.3033) 
(list 320.4503 868.3136) 
(list 320.4503 868.3239) 
(list 320.4503 868.3342) 
(list 320.4503 868.3444) 
(list 320.4503 868.3547) 
(list 320.4503 868.365) 
(list 320.4503 868.3753) 
(list 320.4503 868.3856) 
(list 320.4503 868.3958) 
(list 320.4503 868.4061) 
(list 320.4503 868.4164) 
(list 320.4503 868.4267) 
(list 320.4503 868.4369) 
(list 320.4503 868.4472) 
(list 320.4503 868.4575) 
(list 320.4503 868.4678) 
(list 320.4503 868.4781) 
(list 320.4503 868.4883) 
(list 320.4503 868.4986) 
(list 320.4503 868.5089) 
(list 320.4503 868.5192) 
(list 320.4503 868.5294) 
(list 320.4503 868.5397) 
(list 320.4503 868.55) 
(list 321.082 868.55)))
(apply 'command (append '("pline") coords '("c")))
(setq tap1 (ssadd (entlast) tap1))
(command "_mirror" (entlast) "" "320,900" "320,901" "No")
(setq tap1 (ssadd (entlast) tap1))
(setq coords (list 
(list 320 868.55) 
(list 320.125 868.55) 
(list 320.125 868.5603) 
(list 320.125 868.5706) 
(list 320.125 868.5808) 
(list 320.125 868.5911) 
(list 320.125 868.6014) 
(list 320.125 868.6117) 
(list 320.125 868.6219) 
(list 320.125 868.6322) 
(list 320.125 868.6425) 
(list 320.125 868.6528) 
(list 320.125 868.6631) 
(list 320.125 868.6733) 
(list 320.125 868.6836) 
(list 320.125 868.6939) 
(list 320.125 868.7042) 
(list 320.125 868.7144) 
(list 320.125 868.7247) 
(list 320.125 868.735) 
(list 320.125 868.7453) 
(list 320.125 868.7556) 
(list 320.125 868.7658) 
(list 320.125 868.7761) 
(list 320.125 868.7864) 
(list 320.125 868.7967) 
(list 320.125 868.8069) 
(list 320.125 868.8172) 
(list 320.125 868.8275) 
(list 320.125 868.8378) 
(list 320.125 868.8481) 
(list 320.125 868.8583) 
(list 320.125 868.8686) 
(list 320.125 868.8789) 
(list 320.125 868.8892) 
(list 320.125 868.8994) 
(list 320.125 868.9097) 
(list 320.125 868.92) 
(list 320 868.92)))
(apply 'command (append '("pline") coords '("c")))
(setq tap1 (ssadd (entlast) tap1))
(command "_mirror" (entlast) "" "320,900" "320,901" "No")
(setq tap1 (ssadd (entlast) tap1))
(setq coords (list 
(list 320.4594 868.55) 
(list 320.4503 868.55) 
(list 320.4499 868.5603) 
(list 320.4483 868.5706) 
(list 320.4453 868.5808) 
(list 320.4412 868.5911) 
(list 320.4361 868.6014) 
(list 320.43 868.6117) 
(list 320.4232 868.6219) 
(list 320.4158 868.6322) 
(list 320.4081 868.6425) 
(list 320.4004 868.6528) 
(list 320.3928 868.6631) 
(list 320.3856 868.6733) 
(list 320.379 868.6836) 
(list 320.3733 868.6939) 
(list 320.3685 868.7042) 
(list 320.365 868.7144) 
(list 320.3627 868.7247) 
(list 320.3617 868.735) 
(list 320.3622 868.7453) 
(list 320.3641 868.7556) 
(list 320.3674 868.7658) 
(list 320.372 868.7761) 
(list 320.3777 868.7864) 
(list 320.3844 868.7967) 
(list 320.3919 868.8069) 
(list 320.4 868.8172) 
(list 320.4085 868.8275) 
(list 320.417 868.8378) 
(list 320.4253 868.8481) 
(list 320.4332 868.8583) 
(list 320.4404 868.8686) 
(list 320.4467 868.8789) 
(list 320.4519 868.8892) 
(list 320.4559 868.8994) 
(list 320.4584 868.9097) 
(list 320.4594 868.92) 
(list 320.4594 868.92)))
(apply 'command (append '("pline") coords '("c")))
(setq tap1 (ssadd (entlast) tap1))
(command "_mirror" (entlast) "" "320,900" "320,901" "No")
(setq tap1 (ssadd (entlast) tap1))
(setq coords (list 
(list 321.082 868.55) 
(list 320.4594 868.55) 
(list 320.4594 868.5603) 
(list 320.4594 868.5706) 
(list 320.4594 868.5808) 
(list 320.4594 868.5911) 
(list 320.4594 868.6014) 
(list 320.4594 868.6117) 
(list 320.4594 868.6219) 
(list 320.4594 868.6322) 
(list 320.4594 868.6425) 
(list 320.4594 868.6528) 
(list 320.4594 868.6631) 
(list 320.4594 868.6733) 
(list 320.4594 868.6836) 
(list 320.4594 868.6939) 
(list 320.4594 868.7042) 
(list 320.4594 868.7144) 
(list 320.4594 868.7247) 
(list 320.4594 868.735) 
(list 320.4594 868.7453) 
(list 320.4594 868.7556) 
(list 320.4594 868.7658) 
(list 320.4594 868.7761) 
(list 320.4594 868.7864) 
(list 320.4594 868.7967) 
(list 320.4594 868.8069) 
(list 320.4594 868.8172) 
(list 320.4594 868.8275) 
(list 320.4594 868.8378) 
(list 320.4594 868.8481) 
(list 320.4594 868.8583) 
(list 320.4594 868.8686) 
(list 320.4594 868.8789) 
(list 320.4594 868.8892) 
(list 320.4594 868.8994) 
(list 320.4594 868.9097) 
(list 320.4594 868.92) 
(list 321.082 868.92)))
(apply 'command (append '("pline") coords '("c")))
(setq tap1 (ssadd (entlast) tap1))
(command "_mirror" (entlast) "" "320,900" "320,901" "No")
(setq tap1 (ssadd (entlast) tap1))
(setq coords (list 
(list 320 868.92) 
(list 320.125 868.92) 
(list 320.125 868.9303) 
(list 320.125 868.9406) 
(list 320.125 868.9508) 
(list 320.125 868.9611) 
(list 320.125 868.9714) 
(list 320.125 868.9817) 
(list 320.125 868.9919) 
(list 320.125 869.0022) 
(list 320.125 869.0125) 
(list 320.125 869.0228) 
(list 320.125 869.0331) 
(list 320.125 869.0433) 
(list 320.125 869.0536) 
(list 320.125 869.0639) 
(list 320.125 869.0742) 
(list 320.125 869.0844) 
(list 320.125 869.0947) 
(list 320.125 869.105) 
(list 320.125 869.1153) 
(list 320.125 869.1256) 
(list 320.125 869.1358) 
(list 320.125 869.1461) 
(list 320.125 869.1564) 
(list 320.125 869.1667) 
(list 320.125 869.1769) 
(list 320.125 869.1872) 
(list 320.125 869.1975) 
(list 320.125 869.2078) 
(list 320.125 869.2181) 
(list 320.125 869.2283) 
(list 320.125 869.2386) 
(list 320.125 869.2489) 
(list 320.125 869.2592) 
(list 320.125 869.2694) 
(list 320.125 869.2797) 
(list 320.125 869.29) 
(list 320 869.29)))
(apply 'command (append '("pline") coords '("c")))
(setq tap1 (ssadd (entlast) tap1))
(command "_mirror" (entlast) "" "320,900" "320,901" "No")
(setq tap1 (ssadd (entlast) tap1))
(setq coords (list 
(list 320.4685 868.92) 
(list 320.4594 868.92) 
(list 320.4589 868.9303) 
(list 320.4568 868.9406) 
(list 320.4533 868.9508) 
(list 320.4483 868.9611) 
(list 320.4421 868.9714) 
(list 320.4348 868.9817) 
(list 320.4267 868.9919) 
(list 320.4179 869.0022) 
(list 320.4087 869.0125) 
(list 320.3995 869.0228) 
(list 320.3905 869.0331) 
(list 320.382 869.0433) 
(list 320.3742 869.0536) 
(list 320.3674 869.0639) 
(list 320.3618 869.0742) 
(list 320.3576 869.0844) 
(list 320.3549 869.0947) 
(list 320.3539 869.105) 
(list 320.3545 869.1153) 
(list 320.3568 869.1256) 
(list 320.3607 869.1358) 
(list 320.3661 869.1461) 
(list 320.3729 869.1564) 
(list 320.3808 869.1667) 
(list 320.3896 869.1769) 
(list 320.3992 869.1872) 
(list 320.409 869.1975) 
(list 320.419 869.2078) 
(list 320.4288 869.2181) 
(list 320.438 869.2283) 
(list 320.4465 869.2386) 
(list 320.4538 869.2489) 
(list 320.4599 869.2592) 
(list 320.4644 869.2694) 
(list 320.4673 869.2797) 
(list 320.4685 869.29) 
(list 320.4685 869.29)))
(apply 'command (append '("pline") coords '("c")))
(setq tap1 (ssadd (entlast) tap1))
(command "_mirror" (entlast) "" "320,900" "320,901" "No")
(setq tap1 (ssadd (entlast) tap1))
(setq coords (list 
(list 321.082 868.92) 
(list 320.4685 868.92) 
(list 320.4685 868.9303) 
(list 320.4685 868.9406) 
(list 320.4685 868.9508) 
(list 320.4685 868.9611) 
(list 320.4685 868.9714) 
(list 320.4685 868.9817) 
(list 320.4685 868.9919) 
(list 320.4685 869.0022) 
(list 320.4685 869.0125) 
(list 320.4685 869.0228) 
(list 320.4685 869.0331) 
(list 320.4685 869.0433) 
(list 320.4685 869.0536) 
(list 320.4685 869.0639) 
(list 320.4685 869.0742) 
(list 320.4685 869.0844) 
(list 320.4685 869.0947) 
(list 320.4685 869.105) 
(list 320.4685 869.1153) 
(list 320.4685 869.1256) 
(list 320.4685 869.1358) 
(list 320.4685 869.1461) 
(list 320.4685 869.1564) 
(list 320.4685 869.1667) 
(list 320.4685 869.1769) 
(list 320.4685 869.1872) 
(list 320.4685 869.1975) 
(list 320.4685 869.2078) 
(list 320.4685 869.2181) 
(list 320.4685 869.2283) 
(list 320.4685 869.2386) 
(list 320.4685 869.2489) 
(list 320.4685 869.2592) 
(list 320.4685 869.2694) 
(list 320.4685 869.2797) 
(list 320.4685 869.29) 
(list 321.082 869.29)))
(apply 'command (append '("pline") coords '("c")))
(setq tap1 (ssadd (entlast) tap1))
(command "_mirror" (entlast) "" "320,900" "320,901" "No")
(setq tap1 (ssadd (entlast) tap1))
(setq coords (list 
(list 320 869.29) 
(list 320.125 869.29) 
(list 320.125 869.3003) 
(list 320.125 869.3106) 
(list 320.125 869.3208) 
(list 320.125 869.3311) 
(list 320.125 869.3414) 
(list 320.125 869.3517) 
(list 320.125 869.3619) 
(list 320.125 869.3722) 
(list 320.125 869.3825) 
(list 320.125 869.3928) 
(list 320.125 869.4031) 
(list 320.125 869.4133) 
(list 320.125 869.4236) 
(list 320.125 869.4339) 
(list 320.125 869.4442) 
(list 320.125 869.4544) 
(list 320.125 869.4647) 
(list 320.125 869.475) 
(list 320.125 869.4853) 
(list 320.125 869.4956) 
(list 320.125 869.5058) 
(list 320.125 869.5161) 
(list 320.125 869.5264) 
(list 320.125 869.5367) 
(list 320.125 869.5469) 
(list 320.125 869.5572) 
(list 320.125 869.5675) 
(list 320.125 869.5778) 
(list 320.125 869.5881) 
(list 320.125 869.5983) 
(list 320.125 869.6086) 
(list 320.125 869.6189) 
(list 320.125 869.6292) 
(list 320.125 869.6394) 
(list 320.125 869.6497) 
(list 320.125 869.66) 
(list 320 869.66)))
(apply 'command (append '("pline") coords '("c")))
(setq tap1 (ssadd (entlast) tap1))
(command "_mirror" (entlast) "" "320,900" "320,901" "No")
(setq tap1 (ssadd (entlast) tap1))
(setq coords (list 
(list 320.4775 869.29) 
(list 320.4685 869.29) 
(list 320.4678 869.3003) 
(list 320.4654 869.3106) 
(list 320.4612 869.3208) 
(list 320.4554 869.3311) 
(list 320.4481 869.3414) 
(list 320.4396 869.3517) 
(list 320.4302 869.3619) 
(list 320.42 869.3722) 
(list 320.4094 869.3825) 
(list 320.3987 869.3928) 
(list 320.3882 869.4031) 
(list 320.3784 869.4133) 
(list 320.3694 869.4236) 
(list 320.3615 869.4339) 
(list 320.3551 869.4442) 
(list 320.3502 869.4544) 
(list 320.3472 869.4647) 
(list 320.346 869.475) 
(list 320.3467 869.4853) 
(list 320.3494 869.4956) 
(list 320.3539 869.5058) 
(list 320.3602 869.5161) 
(list 320.368 869.5264) 
(list 320.3771 869.5367) 
(list 320.3873 869.5469) 
(list 320.3983 869.5572) 
(list 320.4096 869.5675) 
(list 320.4211 869.5778) 
(list 320.4323 869.5881) 
(list 320.4429 869.5983) 
(list 320.4525 869.6086) 
(list 320.4609 869.6189) 
(list 320.4678 869.6292) 
(list 320.473 869.6394) 
(list 320.4763 869.6497) 
(list 320.4775 869.66) 
(list 320.4775 869.66)))
(apply 'command (append '("pline") coords '("c")))
(setq tap1 (ssadd (entlast) tap1))
(command "_mirror" (entlast) "" "320,900" "320,901" "No")
(setq tap1 (ssadd (entlast) tap1))
(setq coords (list 
(list 321.082 869.29) 
(list 320.4775 869.29) 
(list 320.4775 869.3003) 
(list 320.4775 869.3106) 
(list 320.4775 869.3208) 
(list 320.4775 869.3311) 
(list 320.4775 869.3414) 
(list 320.4775 869.3517) 
(list 320.4775 869.3619) 
(list 320.4775 869.3722) 
(list 320.4775 869.3825) 
(list 320.4775 869.3928) 
(list 320.4775 869.4031) 
(list 320.4775 869.4133) 
(list 320.4775 869.4236) 
(list 320.4775 869.4339) 
(list 320.4775 869.4442) 
(list 320.4775 869.4544) 
(list 320.4775 869.4647) 
(list 320.4775 869.475) 
(list 320.4775 869.4853) 
(list 320.4775 869.4956) 
(list 320.4775 869.5058) 
(list 320.4775 869.5161) 
(list 320.4775 869.5264) 
(list 320.4775 869.5367) 
(list 320.4775 869.5469) 
(list 320.4775 869.5572) 
(list 320.4775 869.5675) 
(list 320.4775 869.5778) 
(list 320.4775 869.5881) 
(list 320.4775 869.5983) 
(list 320.4775 869.6086) 
(list 320.4775 869.6189) 
(list 320.4775 869.6292) 
(list 320.4775 869.6394) 
(list 320.4775 869.6497) 
(list 320.4775 869.66) 
(list 321.082 869.66)))
(apply 'command (append '("pline") coords '("c")))
(setq tap1 (ssadd (entlast) tap1))
(command "_mirror" (entlast) "" "320,900" "320,901" "No")
(setq tap1 (ssadd (entlast) tap1))
(setq coords (list 
(list 320 869.66) 
(list 320.125 869.66) 
(list 320.125 869.6703) 
(list 320.125 869.6806) 
(list 320.125 869.6908) 
(list 320.125 869.7011) 
(list 320.125 869.7114) 
(list 320.125 869.7217) 
(list 320.125 869.7319) 
(list 320.125 869.7422) 
(list 320.125 869.7525) 
(list 320.125 869.7628) 
(list 320.125 869.7731) 
(list 320.125 869.7833) 
(list 320.125 869.7936) 
(list 320.125 869.8039) 
(list 320.125 869.8142) 
(list 320.125 869.8244) 
(list 320.125 869.8347) 
(list 320.125 869.845) 
(list 320.125 869.8553) 
(list 320.125 869.8656) 
(list 320.125 869.8758) 
(list 320.125 869.8861) 
(list 320.125 869.8964) 
(list 320.125 869.9067) 
(list 320.125 869.9169) 
(list 320.125 869.9272) 
(list 320.125 869.9375) 
(list 320.125 869.9478) 
(list 320.125 869.9581) 
(list 320.125 869.9683) 
(list 320.125 869.9786) 
(list 320.125 869.9889) 
(list 320.125 869.9992) 
(list 320.125 870.0094) 
(list 320.125 870.0197) 
(list 320.125 870.03) 
(list 320 870.03)))
(apply 'command (append '("pline") coords '("c")))
(setq tap1 (ssadd (entlast) tap1))
(command "_mirror" (entlast) "" "320,900" "320,901" "No")
(setq tap1 (ssadd (entlast) tap1))
(setq coords (list 
(list 320.4866 869.66) 
(list 320.4775 869.66) 
(list 320.4768 869.6703) 
(list 320.4739 869.6806) 
(list 320.4691 869.6908) 
(list 320.4625 869.7011) 
(list 320.4542 869.7114) 
(list 320.4445 869.7217) 
(list 320.4336 869.7319) 
(list 320.422 869.7422) 
(list 320.4099 869.7525) 
(list 320.3978 869.7628) 
(list 320.3859 869.7731) 
(list 320.3747 869.7833) 
(list 320.3645 869.7936) 
(list 320.3556 869.8039) 
(list 320.3483 869.8142) 
(list 320.3429 869.8244) 
(list 320.3394 869.8347) 
(list 320.3381 869.845) 
(list 320.339 869.8553) 
(list 320.3421 869.8656) 
(list 320.3472 869.8758) 
(list 320.3543 869.8861) 
(list 320.3632 869.8964) 
(list 320.3735 869.9067) 
(list 320.385 869.9169) 
(list 320.3974 869.9272) 
(list 320.4103 869.9375) 
(list 320.4232 869.9478) 
(list 320.4358 869.9581) 
(list 320.4477 869.9683) 
(list 320.4585 869.9786) 
(list 320.468 869.9889) 
(list 320.4757 869.9992) 
(list 320.4815 870.0094) 
(list 320.4852 870.0197) 
(list 320.4866 870.03) 
(list 320.4866 870.03)))
(apply 'command (append '("pline") coords '("c")))
(setq tap1 (ssadd (entlast) tap1))
(command "_mirror" (entlast) "" "320,900" "320,901" "No")
(setq tap1 (ssadd (entlast) tap1))
(setq coords (list 
(list 321.082 869.66) 
(list 320.4866 869.66) 
(list 320.4866 869.6703) 
(list 320.4866 869.6806) 
(list 320.4866 869.6908) 
(list 320.4866 869.7011) 
(list 320.4866 869.7114) 
(list 320.4866 869.7217) 
(list 320.4866 869.7319) 
(list 320.4866 869.7422) 
(list 320.4866 869.7525) 
(list 320.4866 869.7628) 
(list 320.4866 869.7731) 
(list 320.4866 869.7833) 
(list 320.4866 869.7936) 
(list 320.4866 869.8039) 
(list 320.4866 869.8142) 
(list 320.4866 869.8244) 
(list 320.4866 869.8347) 
(list 320.4866 869.845) 
(list 320.4866 869.8553) 
(list 320.4866 869.8656) 
(list 320.4866 869.8758) 
(list 320.4866 869.8861) 
(list 320.4866 869.8964) 
(list 320.4866 869.9067) 
(list 320.4866 869.9169) 
(list 320.4866 869.9272) 
(list 320.4866 869.9375) 
(list 320.4866 869.9478) 
(list 320.4866 869.9581) 
(list 320.4866 869.9683) 
(list 320.4866 869.9786) 
(list 320.4866 869.9889) 
(list 320.4866 869.9992) 
(list 320.4866 870.0094) 
(list 320.4866 870.0197) 
(list 320.4866 870.03) 
(list 321.082 870.03)))
(apply 'command (append '("pline") coords '("c")))
(setq tap1 (ssadd (entlast) tap1))
(command "_mirror" (entlast) "" "320,900" "320,901" "No")
(setq tap1 (ssadd (entlast) tap1))
(setq coords (list 
(list 320 870.03) 
(list 320.125 870.03) 
(list 320.125 870.0403) 
(list 320.125 870.0506) 
(list 320.125 870.0608) 
(list 320.125 870.0711) 
(list 320.125 870.0814) 
(list 320.125 870.0917) 
(list 320.125 870.1019) 
(list 320.125 870.1122) 
(list 320.125 870.1225) 
(list 320.125 870.1328) 
(list 320.125 870.1431) 
(list 320.125 870.1533) 
(list 320.125 870.1636) 
(list 320.125 870.1739) 
(list 320.125 870.1842) 
(list 320.125 870.1944) 
(list 320.125 870.2047) 
(list 320.125 870.215) 
(list 320.125 870.2253) 
(list 320.125 870.2356) 
(list 320.125 870.2458) 
(list 320.125 870.2561) 
(list 320.125 870.2664) 
(list 320.125 870.2767) 
(list 320.125 870.2869) 
(list 320.125 870.2972) 
(list 320.125 870.3075) 
(list 320.125 870.3178) 
(list 320.125 870.3281) 
(list 320.125 870.3383) 
(list 320.125 870.3486) 
(list 320.125 870.3589) 
(list 320.125 870.3692) 
(list 320.125 870.3794) 
(list 320.125 870.3897) 
(list 320.125 870.4) 
(list 320 870.4)))
(apply 'command (append '("pline") coords '("c")))
(setq tap1 (ssadd (entlast) tap1))
(command "_mirror" (entlast) "" "320,900" "320,901" "No")
(setq tap1 (ssadd (entlast) tap1))
(setq coords (list 
(list 320.4957 870.03) 
(list 320.4866 870.03) 
(list 320.4857 870.0403) 
(list 320.4825 870.0506) 
(list 320.4771 870.0608) 
(list 320.4696 870.0711) 
(list 320.4602 870.0814) 
(list 320.4493 870.0917) 
(list 320.4371 870.1019) 
(list 320.4241 870.1122) 
(list 320.4106 870.1225) 
(list 320.3969 870.1328) 
(list 320.3836 870.1431) 
(list 320.3711 870.1533) 
(list 320.3597 870.1636) 
(list 320.3497 870.1739) 
(list 320.3416 870.1842) 
(list 320.3355 870.1944) 
(list 320.3317 870.2047) 
(list 320.3303 870.215) 
(list 320.3313 870.2253) 
(list 320.3347 870.2356) 
(list 320.3405 870.2458) 
(list 320.3484 870.2561) 
(list 320.3583 870.2664) 
(list 320.3699 870.2767) 
(list 320.3827 870.2869) 
(list 320.3965 870.2972) 
(list 320.4108 870.3075) 
(list 320.4252 870.3178) 
(list 320.4393 870.3281) 
(list 320.4525 870.3383) 
(list 320.4646 870.3486) 
(list 320.4751 870.3589) 
(list 320.4837 870.3692) 
(list 320.4901 870.3794) 
(list 320.4941 870.3897) 
(list 320.4957 870.4) 
(list 320.4957 870.4)))
(apply 'command (append '("pline") coords '("c")))
(setq tap1 (ssadd (entlast) tap1))
(command "_mirror" (entlast) "" "320,900" "320,901" "No")
(setq tap1 (ssadd (entlast) tap1))
(setq coords (list 
(list 321.082 870.03) 
(list 320.4957 870.03) 
(list 320.4957 870.0403) 
(list 320.4957 870.0506) 
(list 320.4957 870.0608) 
(list 320.4957 870.0711) 
(list 320.4957 870.0814) 
(list 320.4957 870.0917) 
(list 320.4957 870.1019) 
(list 320.4957 870.1122) 
(list 320.4957 870.1225) 
(list 320.4957 870.1328) 
(list 320.4957 870.1431) 
(list 320.4957 870.1533) 
(list 320.4957 870.1636) 
(list 320.4957 870.1739) 
(list 320.4957 870.1842) 
(list 320.4957 870.1944) 
(list 320.4957 870.2047) 
(list 320.4957 870.215) 
(list 320.4957 870.2253) 
(list 320.4957 870.2356) 
(list 320.4957 870.2458) 
(list 320.4957 870.2561) 
(list 320.4957 870.2664) 
(list 320.4957 870.2767) 
(list 320.4957 870.2869) 
(list 320.4957 870.2972) 
(list 320.4957 870.3075) 
(list 320.4957 870.3178) 
(list 320.4957 870.3281) 
(list 320.4957 870.3383) 
(list 320.4957 870.3486) 
(list 320.4957 870.3589) 
(list 320.4957 870.3692) 
(list 320.4957 870.3794) 
(list 320.4957 870.3897) 
(list 320.4957 870.4) 
(list 321.082 870.4)))
(apply 'command (append '("pline") coords '("c")))
(setq tap1 (ssadd (entlast) tap1))
(command "_mirror" (entlast) "" "320,900" "320,901" "No")
(setq tap1 (ssadd (entlast) tap1))
(setq coords (list 
(list 320 870.4) 
(list 320.125 870.4) 
(list 320.125 870.4103) 
(list 320.125 870.4206) 
(list 320.125 870.4308) 
(list 320.125 870.4411) 
(list 320.125 870.4514) 
(list 320.125 870.4617) 
(list 320.125 870.4719) 
(list 320.125 870.4822) 
(list 320.125 870.4925) 
(list 320.125 870.5028) 
(list 320.125 870.5131) 
(list 320.125 870.5233) 
(list 320.125 870.5336) 
(list 320.125 870.5439) 
(list 320.125 870.5542) 
(list 320.125 870.5644) 
(list 320.125 870.5747) 
(list 320.125 870.585) 
(list 320.125 870.5953) 
(list 320.125 870.6056) 
(list 320.125 870.6158) 
(list 320.125 870.6261) 
(list 320.125 870.6364) 
(list 320.125 870.6467) 
(list 320.125 870.6569) 
(list 320.125 870.6672) 
(list 320.125 870.6775) 
(list 320.125 870.6878) 
(list 320.125 870.6981) 
(list 320.125 870.7083) 
(list 320.125 870.7186) 
(list 320.125 870.7289) 
(list 320.125 870.7392) 
(list 320.125 870.7494) 
(list 320.125 870.7597) 
(list 320.125 870.77) 
(list 320 870.77)))
(apply 'command (append '("pline") coords '("c")))
(setq tap1 (ssadd (entlast) tap1))
(command "_mirror" (entlast) "" "320,900" "320,901" "No")
(setq tap1 (ssadd (entlast) tap1))
(setq coords (list 
(list 320.5047 870.4) 
(list 320.4957 870.4) 
(list 320.4946 870.4103) 
(list 320.491 870.4206) 
(list 320.485 870.4308) 
(list 320.4766 870.4411) 
(list 320.4663 870.4514) 
(list 320.4541 870.4617) 
(list 320.4406 870.4719) 
(list 320.4262 870.4822) 
(list 320.4112 870.4925) 
(list 320.3961 870.5028) 
(list 320.3813 870.5131) 
(list 320.3675 870.5233) 
(list 320.3548 870.5336) 
(list 320.3439 870.5439) 
(list 320.3349 870.5542) 
(list 320.3282 870.5644) 
(list 320.324 870.5747) 
(list 320.3224 870.585) 
(list 320.3235 870.5953) 
(list 320.3274 870.6056) 
(list 320.3337 870.6158) 
(list 320.3425 870.6261) 
(list 320.3535 870.6364) 
(list 320.3662 870.6467) 
(list 320.3804 870.6569) 
(list 320.3957 870.6672) 
(list 320.4115 870.6775) 
(list 320.4273 870.6878) 
(list 320.4428 870.6981) 
(list 320.4574 870.7083) 
(list 320.4706 870.7186) 
(list 320.4822 870.7289) 
(list 320.4916 870.7392) 
(list 320.4986 870.7494) 
(list 320.5031 870.7597) 
(list 320.5047 870.77) 
(list 320.5047 870.77)))
(apply 'command (append '("pline") coords '("c")))
(setq tap1 (ssadd (entlast) tap1))
(command "_mirror" (entlast) "" "320,900" "320,901" "No")
(setq tap1 (ssadd (entlast) tap1))
(setq coords (list 
(list 321.082 870.4) 
(list 320.5047 870.4) 
(list 320.5047 870.4103) 
(list 320.5047 870.4206) 
(list 320.5047 870.4308) 
(list 320.5047 870.4411) 
(list 320.5047 870.4514) 
(list 320.5047 870.4617) 
(list 320.5047 870.4719) 
(list 320.5047 870.4822) 
(list 320.5047 870.4925) 
(list 320.5047 870.5028) 
(list 320.5047 870.5131) 
(list 320.5047 870.5233) 
(list 320.5047 870.5336) 
(list 320.5047 870.5439) 
(list 320.5047 870.5542) 
(list 320.5047 870.5644) 
(list 320.5047 870.5747) 
(list 320.5047 870.585) 
(list 320.5047 870.5953) 
(list 320.5047 870.6056) 
(list 320.5047 870.6158) 
(list 320.5047 870.6261) 
(list 320.5047 870.6364) 
(list 320.5047 870.6467) 
(list 320.5047 870.6569) 
(list 320.5047 870.6672) 
(list 320.5047 870.6775) 
(list 320.5047 870.6878) 
(list 320.5047 870.6981) 
(list 320.5047 870.7083) 
(list 320.5047 870.7186) 
(list 320.5047 870.7289) 
(list 320.5047 870.7392) 
(list 320.5047 870.7494) 
(list 320.5047 870.7597) 
(list 320.5047 870.77) 
(list 321.082 870.77)))
(apply 'command (append '("pline") coords '("c")))
(setq tap1 (ssadd (entlast) tap1))
(command "_mirror" (entlast) "" "320,900" "320,901" "No")
(setq tap1 (ssadd (entlast) tap1))
(setq coords (list 
(list 320 870.77) 
(list 320.125 870.77) 
(list 320.125 870.7803) 
(list 320.125 870.7906) 
(list 320.125 870.8008) 
(list 320.125 870.8111) 
(list 320.125 870.8214) 
(list 320.125 870.8317) 
(list 320.125 870.8419) 
(list 320.125 870.8522) 
(list 320.125 870.8625) 
(list 320.125 870.8728) 
(list 320.125 870.8831) 
(list 320.125 870.8933) 
(list 320.125 870.9036) 
(list 320.125 870.9139) 
(list 320.125 870.9242) 
(list 320.125 870.9344) 
(list 320.125 870.9447) 
(list 320.125 870.955) 
(list 320.125 870.9653) 
(list 320.125 870.9756) 
(list 320.125 870.9858) 
(list 320.125 870.9961) 
(list 320.125 871.0064) 
(list 320.125 871.0167) 
(list 320.125 871.0269) 
(list 320.125 871.0372) 
(list 320.125 871.0475) 
(list 320.125 871.0578) 
(list 320.125 871.0681) 
(list 320.125 871.0783) 
(list 320.125 871.0886) 
(list 320.125 871.0989) 
(list 320.125 871.1092) 
(list 320.125 871.1194) 
(list 320.125 871.1297) 
(list 320.125 871.14) 
(list 320 871.14)))
(apply 'command (append '("pline") coords '("c")))
(setq tap1 (ssadd (entlast) tap1))
(command "_mirror" (entlast) "" "320,900" "320,901" "No")
(setq tap1 (ssadd (entlast) tap1))
(setq coords (list 
(list 320.5138 870.77) 
(list 320.5047 870.77) 
(list 320.5036 870.7803) 
(list 320.4996 870.7906) 
(list 320.4929 870.8008) 
(list 320.4837 870.8111) 
(list 320.4723 870.8214) 
(list 320.459 870.8317) 
(list 320.4441 870.8419) 
(list 320.4282 870.8522) 
(list 320.4117 870.8625) 
(list 320.3952 870.8728) 
(list 320.379 870.8831) 
(list 320.3638 870.8933) 
(list 320.35 870.9036) 
(list 320.338 870.9139) 
(list 320.3281 870.9242) 
(list 320.3208 870.9344) 
(list 320.3162 870.9447) 
(list 320.3145 870.955) 
(list 320.3158 870.9653) 
(list 320.32 870.9756) 
(list 320.327 870.9858) 
(list 320.3367 870.9961) 
(list 320.3486 871.0064) 
(list 320.3626 871.0167) 
(list 320.3782 871.0269) 
(list 320.3948 871.0372) 
(list 320.4121 871.0475) 
(list 320.4294 871.0578) 
(list 320.4463 871.0681) 
(list 320.4622 871.0783) 
(list 320.4767 871.0886) 
(list 320.4892 871.0989) 
(list 320.4995 871.1092) 
(list 320.5072 871.1194) 
(list 320.512 871.1297) 
(list 320.5138 871.14) 
(list 320.5138 871.14)))
(apply 'command (append '("pline") coords '("c")))
(setq tap1 (ssadd (entlast) tap1))
(command "_mirror" (entlast) "" "320,900" "320,901" "No")
(setq tap1 (ssadd (entlast) tap1))
(setq coords (list 
(list 321.082 870.77) 
(list 320.5138 870.77) 
(list 320.5138 870.7803) 
(list 320.5138 870.7906) 
(list 320.5138 870.8008) 
(list 320.5138 870.8111) 
(list 320.5138 870.8214) 
(list 320.5138 870.8317) 
(list 320.5138 870.8419) 
(list 320.5138 870.8522) 
(list 320.5138 870.8625) 
(list 320.5138 870.8728) 
(list 320.5138 870.8831) 
(list 320.5138 870.8933) 
(list 320.5138 870.9036) 
(list 320.5138 870.9139) 
(list 320.5138 870.9242) 
(list 320.5138 870.9344) 
(list 320.5138 870.9447) 
(list 320.5138 870.955) 
(list 320.5138 870.9653) 
(list 320.5138 870.9756) 
(list 320.5138 870.9858) 
(list 320.5138 870.9961) 
(list 320.5138 871.0064) 
(list 320.5138 871.0167) 
(list 320.5138 871.0269) 
(list 320.5138 871.0372) 
(list 320.5138 871.0475) 
(list 320.5138 871.0578) 
(list 320.5138 871.0681) 
(list 320.5138 871.0783) 
(list 320.5138 871.0886) 
(list 320.5138 871.0989) 
(list 320.5138 871.1092) 
(list 320.5138 871.1194) 
(list 320.5138 871.1297) 
(list 320.5138 871.14) 
(list 321.082 871.14)))
(apply 'command (append '("pline") coords '("c")))
(setq tap1 (ssadd (entlast) tap1))
(command "_mirror" (entlast) "" "320,900" "320,901" "No")
(setq tap1 (ssadd (entlast) tap1))
(setq coords (list 
(list 320 871.14) 
(list 320.125 871.14) 
(list 320.125 871.1503) 
(list 320.125 871.1606) 
(list 320.125 871.1708) 
(list 320.125 871.1811) 
(list 320.125 871.1914) 
(list 320.125 871.2017) 
(list 320.125 871.2119) 
(list 320.125 871.2222) 
(list 320.125 871.2325) 
(list 320.125 871.2428) 
(list 320.125 871.2531) 
(list 320.125 871.2633) 
(list 320.125 871.2736) 
(list 320.125 871.2839) 
(list 320.125 871.2942) 
(list 320.125 871.3044) 
(list 320.125 871.3147) 
(list 320.125 871.325) 
(list 320.125 871.3353) 
(list 320.125 871.3456) 
(list 320.125 871.3558) 
(list 320.125 871.3661) 
(list 320.125 871.3764) 
(list 320.125 871.3867) 
(list 320.125 871.3969) 
(list 320.125 871.4072) 
(list 320.125 871.4175) 
(list 320.125 871.4278) 
(list 320.125 871.4381) 
(list 320.125 871.4483) 
(list 320.125 871.4586) 
(list 320.125 871.4689) 
(list 320.125 871.4792) 
(list 320.125 871.4894) 
(list 320.125 871.4997) 
(list 320.125 871.51) 
(list 320 871.51)))
(apply 'command (append '("pline") coords '("c")))
(setq tap1 (ssadd (entlast) tap1))
(command "_mirror" (entlast) "" "320,900" "320,901" "No")
(setq tap1 (ssadd (entlast) tap1))
(setq coords (list 
(list 320.5229 871.14) 
(list 320.5138 871.14) 
(list 320.5125 871.1503) 
(list 320.5081 871.1606) 
(list 320.5009 871.1708) 
(list 320.4908 871.1811) 
(list 320.4783 871.1914) 
(list 320.4638 871.2017) 
(list 320.4476 871.2119) 
(list 320.4303 871.2222) 
(list 320.4124 871.2325) 
(list 320.3943 871.2428) 
(list 320.3767 871.2531) 
(list 320.3602 871.2633) 
(list 320.3451 871.2736) 
(list 320.3321 871.2839) 
(list 320.3214 871.2942) 
(list 320.3135 871.3044) 
(list 320.3085 871.3147) 
(list 320.3067 871.325) 
(list 320.3081 871.3353) 
(list 320.3126 871.3456) 
(list 320.3203 871.3558) 
(list 320.3308 871.3661) 
(list 320.3438 871.3764) 
(list 320.359 871.3867) 
(list 320.3759 871.3969) 
(list 320.3939 871.4072) 
(list 320.4126 871.4175) 
(list 320.4315 871.4278) 
(list 320.4498 871.4381) 
(list 320.467 871.4483) 
(list 320.4827 871.4586) 
(list 320.4963 871.4689) 
(list 320.5075 871.4792) 
(list 320.5158 871.4894) 
(list 320.5209 871.4997) 
(list 320.5229 871.51) 
(list 320.5229 871.51)))
(apply 'command (append '("pline") coords '("c")))
(setq tap1 (ssadd (entlast) tap1))
(command "_mirror" (entlast) "" "320,900" "320,901" "No")
(setq tap1 (ssadd (entlast) tap1))
(setq coords (list 
(list 321.082 871.14) 
(list 320.5229 871.14) 
(list 320.5229 871.1503) 
(list 320.5229 871.1606) 
(list 320.5229 871.1708) 
(list 320.5229 871.1811) 
(list 320.5229 871.1914) 
(list 320.5229 871.2017) 
(list 320.5229 871.2119) 
(list 320.5229 871.2222) 
(list 320.5229 871.2325) 
(list 320.5229 871.2428) 
(list 320.5229 871.2531) 
(list 320.5229 871.2633) 
(list 320.5229 871.2736) 
(list 320.5229 871.2839) 
(list 320.5229 871.2942) 
(list 320.5229 871.3044) 
(list 320.5229 871.3147) 
(list 320.5229 871.325) 
(list 320.5229 871.3353) 
(list 320.5229 871.3456) 
(list 320.5229 871.3558) 
(list 320.5229 871.3661) 
(list 320.5229 871.3764) 
(list 320.5229 871.3867) 
(list 320.5229 871.3969) 
(list 320.5229 871.4072) 
(list 320.5229 871.4175) 
(list 320.5229 871.4278) 
(list 320.5229 871.4381) 
(list 320.5229 871.4483) 
(list 320.5229 871.4586) 
(list 320.5229 871.4689) 
(list 320.5229 871.4792) 
(list 320.5229 871.4894) 
(list 320.5229 871.4997) 
(list 320.5229 871.51) 
(list 321.082 871.51)))
(apply 'command (append '("pline") coords '("c")))
(setq tap1 (ssadd (entlast) tap1))
(command "_mirror" (entlast) "" "320,900" "320,901" "No")
(setq tap1 (ssadd (entlast) tap1))
(setq coords (list 
(list 320 871.51) 
(list 320.125 871.51) 
(list 320.125 871.5203) 
(list 320.125 871.5306) 
(list 320.125 871.5408) 
(list 320.125 871.5511) 
(list 320.125 871.5614) 
(list 320.125 871.5717) 
(list 320.125 871.5819) 
(list 320.125 871.5922) 
(list 320.125 871.6025) 
(list 320.125 871.6128) 
(list 320.125 871.6231) 
(list 320.125 871.6333) 
(list 320.125 871.6436) 
(list 320.125 871.6539) 
(list 320.125 871.6642) 
(list 320.125 871.6744) 
(list 320.125 871.6847) 
(list 320.125 871.695) 
(list 320.125 871.7053) 
(list 320.125 871.7156) 
(list 320.125 871.7258) 
(list 320.125 871.7361) 
(list 320.125 871.7464) 
(list 320.125 871.7567) 
(list 320.125 871.7669) 
(list 320.125 871.7772) 
(list 320.125 871.7875) 
(list 320.125 871.7978) 
(list 320.125 871.8081) 
(list 320.125 871.8183) 
(list 320.125 871.8286) 
(list 320.125 871.8389) 
(list 320.125 871.8492) 
(list 320.125 871.8594) 
(list 320.125 871.8697) 
(list 320.125 871.88) 
(list 320 871.88)))
(apply 'command (append '("pline") coords '("c")))
(setq tap1 (ssadd (entlast) tap1))
(command "_mirror" (entlast) "" "320,900" "320,901" "No")
(setq tap1 (ssadd (entlast) tap1))
(setq coords (list 
(list 320.5319 871.51) 
(list 320.5229 871.51) 
(list 320.5214 871.5203) 
(list 320.5167 871.5306) 
(list 320.5088 871.5408) 
(list 320.4979 871.5511) 
(list 320.4844 871.5614) 
(list 320.4686 871.5717) 
(list 320.4511 871.5819) 
(list 320.4324 871.5922) 
(list 320.413 871.6025) 
(list 320.3934 871.6128) 
(list 320.3745 871.6231) 
(list 320.3566 871.6333) 
(list 320.3403 871.6436) 
(list 320.3262 871.6539) 
(list 320.3147 871.6642) 
(list 320.3061 871.6744) 
(list 320.3008 871.6847) 
(list 320.2988 871.695) 
(list 320.3003 871.7053) 
(list 320.3053 871.7156) 
(list 320.3136 871.7258) 
(list 320.3249 871.7361) 
(list 320.339 871.7464) 
(list 320.3553 871.7567) 
(list 320.3736 871.7669) 
(list 320.3931 871.7772) 
(list 320.4133 871.7875) 
(list 320.4335 871.7978) 
(list 320.4533 871.8081) 
(list 320.4719 871.8183) 
(list 320.4888 871.8286) 
(list 320.5034 871.8389) 
(list 320.5154 871.8492) 
(list 320.5243 871.8594) 
(list 320.5299 871.8697) 
(list 320.5319 871.88) 
(list 320.5319 871.88)))
(apply 'command (append '("pline") coords '("c")))
(setq tap1 (ssadd (entlast) tap1))
(command "_mirror" (entlast) "" "320,900" "320,901" "No")
(setq tap1 (ssadd (entlast) tap1))
(setq coords (list 
(list 321.082 871.51) 
(list 320.5319 871.51) 
(list 320.5319 871.5203) 
(list 320.5319 871.5306) 
(list 320.5319 871.5408) 
(list 320.5319 871.5511) 
(list 320.5319 871.5614) 
(list 320.5319 871.5717) 
(list 320.5319 871.5819) 
(list 320.5319 871.5922) 
(list 320.5319 871.6025) 
(list 320.5319 871.6128) 
(list 320.5319 871.6231) 
(list 320.5319 871.6333) 
(list 320.5319 871.6436) 
(list 320.5319 871.6539) 
(list 320.5319 871.6642) 
(list 320.5319 871.6744) 
(list 320.5319 871.6847) 
(list 320.5319 871.695) 
(list 320.5319 871.7053) 
(list 320.5319 871.7156) 
(list 320.5319 871.7258) 
(list 320.5319 871.7361) 
(list 320.5319 871.7464) 
(list 320.5319 871.7567) 
(list 320.5319 871.7669) 
(list 320.5319 871.7772) 
(list 320.5319 871.7875) 
(list 320.5319 871.7978) 
(list 320.5319 871.8081) 
(list 320.5319 871.8183) 
(list 320.5319 871.8286) 
(list 320.5319 871.8389) 
(list 320.5319 871.8492) 
(list 320.5319 871.8594) 
(list 320.5319 871.8697) 
(list 320.5319 871.88) 
(list 321.082 871.88)))
(apply 'command (append '("pline") coords '("c")))
(setq tap1 (ssadd (entlast) tap1))
(command "_mirror" (entlast) "" "320,900" "320,901" "No")
(setq tap1 (ssadd (entlast) tap1))
(setq coords (list 
(list 320 871.88) 
(list 320.125 871.88) 
(list 320.125 871.8903) 
(list 320.125 871.9006) 
(list 320.125 871.9108) 
(list 320.125 871.9211) 
(list 320.125 871.9314) 
(list 320.125 871.9417) 
(list 320.125 871.9519) 
(list 320.125 871.9622) 
(list 320.125 871.9725) 
(list 320.125 871.9828) 
(list 320.125 871.9931) 
(list 320.125 872.0033) 
(list 320.125 872.0136) 
(list 320.125 872.0239) 
(list 320.125 872.0342) 
(list 320.125 872.0444) 
(list 320.125 872.0547) 
(list 320.125 872.065) 
(list 320.125 872.0753) 
(list 320.125 872.0856) 
(list 320.125 872.0958) 
(list 320.125 872.1061) 
(list 320.125 872.1164) 
(list 320.125 872.1267) 
(list 320.125 872.1369) 
(list 320.125 872.1472) 
(list 320.125 872.1575) 
(list 320.125 872.1678) 
(list 320.125 872.1781) 
(list 320.125 872.1883) 
(list 320.125 872.1986) 
(list 320.125 872.2089) 
(list 320.125 872.2192) 
(list 320.125 872.2294) 
(list 320.125 872.2397) 
(list 320.125 872.25) 
(list 320 872.25)))
(apply 'command (append '("pline") coords '("c")))
(setq tap1 (ssadd (entlast) tap1))
(command "_mirror" (entlast) "" "320,900" "320,901" "No")
(setq tap1 (ssadd (entlast) tap1))
(setq coords (list 
(list 320.541 871.88) 
(list 320.5319 871.88) 
(list 320.5304 871.8903) 
(list 320.5253 871.9006) 
(list 320.5167 871.9108) 
(list 320.505 871.9211) 
(list 320.4904 871.9314) 
(list 320.4735 871.9417) 
(list 320.4546 871.9519) 
(list 320.4344 871.9622) 
(list 320.4135 871.9725) 
(list 320.3926 871.9828) 
(list 320.3722 871.9931) 
(list 320.3529 872.0033) 
(list 320.3355 872.0136) 
(list 320.3203 872.0239) 
(list 320.3079 872.0342) 
(list 320.2987 872.0444) 
(list 320.293 872.0547) 
(list 320.2909 872.065) 
(list 320.2926 872.0753) 
(list 320.2979 872.0856) 
(list 320.3068 872.0958) 
(list 320.319 872.1061) 
(list 320.3341 872.1164) 
(list 320.3517 872.1267) 
(list 320.3713 872.1369) 
(list 320.3922 872.1472) 
(list 320.4139 872.1575) 
(list 320.4356 872.1678) 
(list 320.4568 872.1781) 
(list 320.4767 872.1883) 
(list 320.4948 872.1986) 
(list 320.5105 872.2089) 
(list 320.5233 872.2192) 
(list 320.5329 872.2294) 
(list 320.5388 872.2397) 
(list 320.541 872.25) 
(list 320.541 872.25)))
(apply 'command (append '("pline") coords '("c")))
(setq tap1 (ssadd (entlast) tap1))
(command "_mirror" (entlast) "" "320,900" "320,901" "No")
(setq tap1 (ssadd (entlast) tap1))
(setq coords (list 
(list 321.082 871.88) 
(list 320.541 871.88) 
(list 320.541 871.8903) 
(list 320.541 871.9006) 
(list 320.541 871.9108) 
(list 320.541 871.9211) 
(list 320.541 871.9314) 
(list 320.541 871.9417) 
(list 320.541 871.9519) 
(list 320.541 871.9622) 
(list 320.541 871.9725) 
(list 320.541 871.9828) 
(list 320.541 871.9931) 
(list 320.541 872.0033) 
(list 320.541 872.0136) 
(list 320.541 872.0239) 
(list 320.541 872.0342) 
(list 320.541 872.0444) 
(list 320.541 872.0547) 
(list 320.541 872.065) 
(list 320.541 872.0753) 
(list 320.541 872.0856) 
(list 320.541 872.0958) 
(list 320.541 872.1061) 
(list 320.541 872.1164) 
(list 320.541 872.1267) 
(list 320.541 872.1369) 
(list 320.541 872.1472) 
(list 320.541 872.1575) 
(list 320.541 872.1678) 
(list 320.541 872.1781) 
(list 320.541 872.1883) 
(list 320.541 872.1986) 
(list 320.541 872.2089) 
(list 320.541 872.2192) 
(list 320.541 872.2294) 
(list 320.541 872.2397) 
(list 320.541 872.25) 
(list 321.082 872.25)))
(apply 'command (append '("pline") coords '("c")))
(setq tap1 (ssadd (entlast) tap1))
(command "_mirror" (entlast) "" "320,900" "320,901" "No")
(setq tap1 (ssadd (entlast) tap1))
(command "_block" "blktap1" "320,900" tap1 "")
(command "_insert" "blktap1" "320,900" "1" "1" "0")
(command "_insert" "blktap1" "320,900" "1" "1" "180")
(setq uc1 nil)
(setq uc1 (ssadd))
(setq coords (list 
(list 0 -0.185) 
(list 0.125 -0.185) 
(list 0.125 -0.17472) 
(list 0.125 -0.16444) 
(list 0.125 -0.15417) 
(list 0.125 -0.14389) 
(list 0.125 -0.13361) 
(list 0.125 -0.12333) 
(list 0.125 -0.11306) 
(list 0.125 -0.10278) 
(list 0.125 -0.0925) 
(list 0.125 -0.082222) 
(list 0.125 -0.071944) 
(list 0.125 -0.061667) 
(list 0.125 -0.051389) 
(list 0.125 -0.041111) 
(list 0.125 -0.030833) 
(list 0.125 -0.020556) 
(list 0.125 -0.010278) 
(list 0.125 0) 
(list 0.125 0.010278) 
(list 0.125 0.020556) 
(list 0.125 0.030833) 
(list 0.125 0.041111) 
(list 0.125 0.051389) 
(list 0.125 0.061667) 
(list 0.125 0.071944) 
(list 0.125 0.082222) 
(list 0.125 0.0925) 
(list 0.125 0.10278) 
(list 0.125 0.11306) 
(list 0.125 0.12333) 
(list 0.125 0.13361) 
(list 0.125 0.14389) 
(list 0.125 0.15417) 
(list 0.125 0.16444) 
(list 0.125 0.17472) 
(list 0.125 0.185) 
(list 0 0.185)))
(apply 'command (append '("pline") coords '("c")))
(setq uc1 (ssadd (entlast) uc1))
(setq coords (list 
(list 1.082 -0.185) 
(list 0.541 -0.185) 
(list 0.53907 -0.17472) 
(list 0.53334 -0.16444) 
(list 0.52399 -0.15417) 
(list 0.51129 -0.14389) 
(list 0.49563 -0.13361) 
(list 0.4775 -0.12333) 
(list 0.45744 -0.11306) 
(list 0.43605 -0.10278) 
(list 0.414 -0.0925) 
(list 0.39195 -0.082222) 
(list 0.37056 -0.071944) 
(list 0.3505 -0.061667) 
(list 0.33237 -0.051389) 
(list 0.31671 -0.041111) 
(list 0.30401 -0.030833) 
(list 0.29466 -0.020556) 
(list 0.28893 -0.010278) 
(list 0.287 0) 
(list 0.28893 0.010278) 
(list 0.29466 0.020556) 
(list 0.30401 0.030833) 
(list 0.31671 0.041111) 
(list 0.33237 0.051389) 
(list 0.3505 0.061667) 
(list 0.37056 0.071944) 
(list 0.39195 0.082222) 
(list 0.414 0.0925) 
(list 0.43605 0.10278) 
(list 0.45744 0.11306) 
(list 0.4775 0.12333) 
(list 0.49563 0.13361) 
(list 0.51129 0.14389) 
(list 0.52399 0.15417) 
(list 0.53334 0.16444) 
(list 0.53907 0.17472) 
(list 0.541 0.185) 
(list 1.082 0.185)))
(apply 'command (append '("pline") coords '("c")))
(setq uc1 (ssadd (entlast) uc1))
(command "_block" "blkuc1" "0,0.185" uc1 "")
(command "_insert" "blkuc1" "320,872.62" "1" "1" "0")
(command "_insert" "blkuc1" "320,872.25" "1" "1" "180")
(command "_insert" "blkuc1" "320,872.99" "1" "1" "0")
(command "_insert" "blkuc1" "320,872.62" "1" "1" "180")
(command "_insert" "blkuc1" "320,873.36" "1" "1" "0")
(command "_insert" "blkuc1" "320,872.99" "1" "1" "180")
(command "_insert" "blkuc1" "320,873.73" "1" "1" "0")
(command "_insert" "blkuc1" "320,873.36" "1" "1" "180")
(command "_insert" "blkuc1" "320,874.1" "1" "1" "0")
(command "_insert" "blkuc1" "320,873.73" "1" "1" "180")
(command "_insert" "blkuc1" "320,874.47" "1" "1" "0")
(command "_insert" "blkuc1" "320,874.1" "1" "1" "180")
(command "_insert" "blkuc1" "320,874.84" "1" "1" "0")
(command "_insert" "blkuc1" "320,874.47" "1" "1" "180")
(command "_insert" "blkuc1" "320,875.21" "1" "1" "0")
(command "_insert" "blkuc1" "320,874.84" "1" "1" "180")
(command "_insert" "blkuc1" "320,875.58" "1" "1" "0")
(command "_insert" "blkuc1" "320,875.21" "1" "1" "180")
(command "_insert" "blkuc1" "320,875.95" "1" "1" "0")
(command "_insert" "blkuc1" "320,875.58" "1" "1" "180")
(command "_insert" "blkuc1" "320,876.32" "1" "1" "0")
(command "_insert" "blkuc1" "320,875.95" "1" "1" "180")
(command "_insert" "blkuc1" "320,876.69" "1" "1" "0")
(command "_insert" "blkuc1" "320,876.32" "1" "1" "180")
(command "_insert" "blkuc1" "320,877.06" "1" "1" "0")
(command "_insert" "blkuc1" "320,876.69" "1" "1" "180")
(command "_insert" "blkuc1" "320,877.43" "1" "1" "0")
(command "_insert" "blkuc1" "320,877.06" "1" "1" "180")
(command "_insert" "blkuc1" "320,877.8" "1" "1" "0")
(command "_insert" "blkuc1" "320,877.43" "1" "1" "180")
(command "_insert" "blkuc1" "320,878.17" "1" "1" "0")
(command "_insert" "blkuc1" "320,877.8" "1" "1" "180")
(command "_insert" "blkuc1" "320,878.54" "1" "1" "0")
(command "_insert" "blkuc1" "320,878.17" "1" "1" "180")
(command "_insert" "blkuc1" "320,878.91" "1" "1" "0")
(command "_insert" "blkuc1" "320,878.54" "1" "1" "180")
(command "_insert" "blkuc1" "320,879.28" "1" "1" "0")
(command "_insert" "blkuc1" "320,878.91" "1" "1" "180")
(command "_insert" "blkuc1" "320,879.65" "1" "1" "0")
(command "_insert" "blkuc1" "320,879.28" "1" "1" "180")
(command "_insert" "blkuc1" "320,880.02" "1" "1" "0")
(command "_insert" "blkuc1" "320,879.65" "1" "1" "180")
(command "_insert" "blkuc1" "320,880.39" "1" "1" "0")
(command "_insert" "blkuc1" "320,880.02" "1" "1" "180")
(command "_insert" "blkuc1" "320,880.76" "1" "1" "0")
(command "_insert" "blkuc1" "320,880.39" "1" "1" "180")
(command "_insert" "blkuc1" "320,881.13" "1" "1" "0")
(command "_insert" "blkuc1" "320,880.76" "1" "1" "180")
(command "_insert" "blkuc1" "320,881.5" "1" "1" "0")
(command "_insert" "blkuc1" "320,881.13" "1" "1" "180")
(command "_insert" "blkuc1" "320,881.87" "1" "1" "0")
(command "_insert" "blkuc1" "320,881.5" "1" "1" "180")
(command "_insert" "blkuc1" "320,882.24" "1" "1" "0")
(command "_insert" "blkuc1" "320,881.87" "1" "1" "180")
(command "_insert" "blkuc1" "320,882.61" "1" "1" "0")
(command "_insert" "blkuc1" "320,882.24" "1" "1" "180")
(command "_insert" "blkuc1" "320,882.98" "1" "1" "0")
(command "_insert" "blkuc1" "320,882.61" "1" "1" "180")
(command "_insert" "blkuc1" "320,883.35" "1" "1" "0")
(command "_insert" "blkuc1" "320,882.98" "1" "1" "180")
(command "_insert" "blkuc1" "320,883.72" "1" "1" "0")
(command "_insert" "blkuc1" "320,883.35" "1" "1" "180")
(command "_insert" "blkuc1" "320,884.09" "1" "1" "0")
(command "_insert" "blkuc1" "320,883.72" "1" "1" "180")
(command "_insert" "blkuc1" "320,884.46" "1" "1" "0")
(command "_insert" "blkuc1" "320,884.09" "1" "1" "180")
(command "_insert" "blkuc1" "320,884.83" "1" "1" "0")
(command "_insert" "blkuc1" "320,884.46" "1" "1" "180")
(command "_insert" "blkuc1" "320,885.2" "1" "1" "0")
(command "_insert" "blkuc1" "320,884.83" "1" "1" "180")
(command "_insert" "blkuc1" "320,885.57" "1" "1" "0")
(command "_insert" "blkuc1" "320,885.2" "1" "1" "180")
(command "_insert" "blkuc1" "320,885.94" "1" "1" "0")
(command "_insert" "blkuc1" "320,885.57" "1" "1" "180")
(command "_insert" "blkuc1" "320,886.31" "1" "1" "0")
(command "_insert" "blkuc1" "320,885.94" "1" "1" "180")
(command "_insert" "blkuc1" "320,886.68" "1" "1" "0")
(command "_insert" "blkuc1" "320,886.31" "1" "1" "180")
(command "_insert" "blkuc1" "320,887.05" "1" "1" "0")
(command "_insert" "blkuc1" "320,886.68" "1" "1" "180")
(command "_insert" "blkuc1" "320,887.42" "1" "1" "0")
(command "_insert" "blkuc1" "320,887.05" "1" "1" "180")
(command "_insert" "blkuc1" "320,887.79" "1" "1" "0")
(command "_insert" "blkuc1" "320,887.42" "1" "1" "180")
(command "_insert" "blkuc1" "320,888.16" "1" "1" "0")
(command "_insert" "blkuc1" "320,887.79" "1" "1" "180")
(command "_insert" "blkuc1" "320,888.53" "1" "1" "0")
(command "_insert" "blkuc1" "320,888.16" "1" "1" "180")
(command "_insert" "blkuc1" "320,888.9" "1" "1" "0")
(command "_insert" "blkuc1" "320,888.53" "1" "1" "180")
(command "_insert" "blkuc1" "320,889.27" "1" "1" "0")
(command "_insert" "blkuc1" "320,888.9" "1" "1" "180")
(command "_insert" "blkuc1" "320,889.64" "1" "1" "0")
(command "_insert" "blkuc1" "320,889.27" "1" "1" "180")
(command "_insert" "blkuc1" "320,890.01" "1" "1" "0")
(command "_insert" "blkuc1" "320,889.64" "1" "1" "180")
(command "_insert" "blkuc1" "320,890.38" "1" "1" "0")
(command "_insert" "blkuc1" "320,890.01" "1" "1" "180")
(command "_insert" "blkuc1" "320,890.75" "1" "1" "0")
(command "_insert" "blkuc1" "320,890.38" "1" "1" "180")
(command "_insert" "blkuc1" "320,891.12" "1" "1" "0")
(command "_insert" "blkuc1" "320,890.75" "1" "1" "180")
(command "_insert" "blkuc1" "320,891.49" "1" "1" "0")
(command "_insert" "blkuc1" "320,891.12" "1" "1" "180")
(command "_insert" "blkuc1" "320,891.86" "1" "1" "0")
(command "_insert" "blkuc1" "320,891.49" "1" "1" "180")
(command "_insert" "blkuc1" "320,892.23" "1" "1" "0")
(command "_insert" "blkuc1" "320,891.86" "1" "1" "180")
(command "_insert" "blkuc1" "320,892.6" "1" "1" "0")
(command "_insert" "blkuc1" "320,892.23" "1" "1" "180")
(command "_insert" "blkuc1" "320,892.97" "1" "1" "0")
(command "_insert" "blkuc1" "320,892.6" "1" "1" "180")
(command "_insert" "blkuc1" "320,893.34" "1" "1" "0")
(command "_insert" "blkuc1" "320,892.97" "1" "1" "180")
(command "_insert" "blkuc1" "320,893.71" "1" "1" "0")
(command "_insert" "blkuc1" "320,893.34" "1" "1" "180")
(command "_insert" "blkuc1" "320,894.08" "1" "1" "0")
(command "_insert" "blkuc1" "320,893.71" "1" "1" "180")
(command "_insert" "blkuc1" "320,894.45" "1" "1" "0")
(command "_insert" "blkuc1" "320,894.08" "1" "1" "180")
(command "_insert" "blkuc1" "320,894.82" "1" "1" "0")
(command "_insert" "blkuc1" "320,894.45" "1" "1" "180")
(command "_insert" "blkuc1" "320,895.19" "1" "1" "0")
(command "_insert" "blkuc1" "320,894.82" "1" "1" "180")
(command "_insert" "blkuc1" "320,895.56" "1" "1" "0")
(command "_insert" "blkuc1" "320,895.19" "1" "1" "180")
(command "_insert" "blkuc1" "320,895.93" "1" "1" "0")
(command "_insert" "blkuc1" "320,895.56" "1" "1" "180")
(command "_insert" "blkuc1" "320,896.3" "1" "1" "0")
(command "_insert" "blkuc1" "320,895.93" "1" "1" "180")
(command "_insert" "blkuc1" "320,896.67" "1" "1" "0")
(command "_insert" "blkuc1" "320,896.3" "1" "1" "180")
(command "_insert" "blkuc1" "320,897.04" "1" "1" "0")
(command "_insert" "blkuc1" "320,896.67" "1" "1" "180")
(command "_insert" "blkuc1" "320,897.41" "1" "1" "0")
(command "_insert" "blkuc1" "320,897.04" "1" "1" "180")
(command "_insert" "blkuc1" "320,897.78" "1" "1" "0")
(command "_insert" "blkuc1" "320,897.41" "1" "1" "180")
(command "_insert" "blkuc1" "320,898.15" "1" "1" "0")
(command "_insert" "blkuc1" "320,897.78" "1" "1" "180")
(command "_insert" "blkuc1" "320,898.52" "1" "1" "0")
(command "_insert" "blkuc1" "320,898.15" "1" "1" "180")
(command "_insert" "blkuc1" "320,898.89" "1" "1" "0")
(command "_insert" "blkuc1" "320,898.52" "1" "1" "180")
(command "_insert" "blkuc1" "320,899.26" "1" "1" "0")
(command "_insert" "blkuc1" "320,898.89" "1" "1" "180")
(command "_insert" "blkuc1" "320,899.63" "1" "1" "0")
(command "_insert" "blkuc1" "320,899.26" "1" "1" "180")
(command "_insert" "blkuc1" "320,900" "1" "1" "0")
(command "_insert" "blkuc1" "320,899.63" "1" "1" "180")
(command "_insert" "blkuc1" "320,900.37" "1" "1" "0")
(command "_insert" "blkuc1" "320,900" "1" "1" "180")
(command "_insert" "blkuc1" "320,900.74" "1" "1" "0")
(command "_insert" "blkuc1" "320,900.37" "1" "1" "180")
(command "_insert" "blkuc1" "320,901.11" "1" "1" "0")
(command "_insert" "blkuc1" "320,900.74" "1" "1" "180")
(command "_insert" "blkuc1" "320,901.48" "1" "1" "0")
(command "_insert" "blkuc1" "320,901.11" "1" "1" "180")
(command "_insert" "blkuc1" "320,901.85" "1" "1" "0")
(command "_insert" "blkuc1" "320,901.48" "1" "1" "180")
(command "_insert" "blkuc1" "320,902.22" "1" "1" "0")
(command "_insert" "blkuc1" "320,901.85" "1" "1" "180")
(command "_insert" "blkuc1" "320,902.59" "1" "1" "0")
(command "_insert" "blkuc1" "320,902.22" "1" "1" "180")
(command "_insert" "blkuc1" "320,902.96" "1" "1" "0")
(command "_insert" "blkuc1" "320,902.59" "1" "1" "180")
(command "_insert" "blkuc1" "320,903.33" "1" "1" "0")
(command "_insert" "blkuc1" "320,902.96" "1" "1" "180")
(command "_insert" "blkuc1" "320,903.7" "1" "1" "0")
(command "_insert" "blkuc1" "320,903.33" "1" "1" "180")
(command "_insert" "blkuc1" "320,904.07" "1" "1" "0")
(command "_insert" "blkuc1" "320,903.7" "1" "1" "180")
(command "_insert" "blkuc1" "320,904.44" "1" "1" "0")
(command "_insert" "blkuc1" "320,904.07" "1" "1" "180")
(command "_insert" "blkuc1" "320,904.81" "1" "1" "0")
(command "_insert" "blkuc1" "320,904.44" "1" "1" "180")
(command "_insert" "blkuc1" "320,905.18" "1" "1" "0")
(command "_insert" "blkuc1" "320,904.81" "1" "1" "180")
(command "_insert" "blkuc1" "320,905.55" "1" "1" "0")
(command "_insert" "blkuc1" "320,905.18" "1" "1" "180")
(command "_insert" "blkuc1" "320,905.92" "1" "1" "0")
(command "_insert" "blkuc1" "320,905.55" "1" "1" "180")
(command "_insert" "blkuc1" "320,906.29" "1" "1" "0")
(command "_insert" "blkuc1" "320,905.92" "1" "1" "180")
(command "_insert" "blkuc1" "320,906.66" "1" "1" "0")
(command "_insert" "blkuc1" "320,906.29" "1" "1" "180")
(command "_insert" "blkuc1" "320,907.03" "1" "1" "0")
(command "_insert" "blkuc1" "320,906.66" "1" "1" "180")
(command "_insert" "blkuc1" "320,907.4" "1" "1" "0")
(command "_insert" "blkuc1" "320,907.03" "1" "1" "180")
(command "_insert" "blkuc1" "320,907.77" "1" "1" "0")
(command "_insert" "blkuc1" "320,907.4" "1" "1" "180")
(command "_insert" "blkuc1" "320,908.14" "1" "1" "0")
(command "_insert" "blkuc1" "320,907.77" "1" "1" "180")
(command "_insert" "blkuc1" "320,908.51" "1" "1" "0")
(command "_insert" "blkuc1" "320,908.14" "1" "1" "180")
(command "_insert" "blkuc1" "320,908.88" "1" "1" "0")
(command "_insert" "blkuc1" "320,908.51" "1" "1" "180")
(command "_insert" "blkuc1" "320,909.25" "1" "1" "0")
(command "_insert" "blkuc1" "320,908.88" "1" "1" "180")
(command "_insert" "blkuc1" "320,909.62" "1" "1" "0")
(command "_insert" "blkuc1" "320,909.25" "1" "1" "180")
(command "_insert" "blkuc1" "320,909.99" "1" "1" "0")
(command "_insert" "blkuc1" "320,909.62" "1" "1" "180")
(command "_insert" "blkuc1" "320,910.36" "1" "1" "0")
(command "_insert" "blkuc1" "320,909.99" "1" "1" "180")
(command "_insert" "blkuc1" "320,910.73" "1" "1" "0")
(command "_insert" "blkuc1" "320,910.36" "1" "1" "180")
(command "_insert" "blkuc1" "320,911.1" "1" "1" "0")
(command "_insert" "blkuc1" "320,910.73" "1" "1" "180")
(command "_insert" "blkuc1" "320,911.47" "1" "1" "0")
(command "_insert" "blkuc1" "320,911.1" "1" "1" "180")
(command "_insert" "blkuc1" "320,911.84" "1" "1" "0")
(command "_insert" "blkuc1" "320,911.47" "1" "1" "180")
(command "_insert" "blkuc1" "320,912.21" "1" "1" "0")
(command "_insert" "blkuc1" "320,911.84" "1" "1" "180")
(command "_insert" "blkuc1" "320,912.58" "1" "1" "0")
(command "_insert" "blkuc1" "320,912.21" "1" "1" "180")
(command "_insert" "blkuc1" "320,912.95" "1" "1" "0")
(command "_insert" "blkuc1" "320,912.58" "1" "1" "180")
(command "_insert" "blkuc1" "320,913.32" "1" "1" "0")
(command "_insert" "blkuc1" "320,912.95" "1" "1" "180")
(command "_insert" "blkuc1" "320,913.69" "1" "1" "0")
(command "_insert" "blkuc1" "320,913.32" "1" "1" "180")
(command "_insert" "blkuc1" "320,914.06" "1" "1" "0")
(command "_insert" "blkuc1" "320,913.69" "1" "1" "180")
(command "_insert" "blkuc1" "320,914.43" "1" "1" "0")
(command "_insert" "blkuc1" "320,914.06" "1" "1" "180")
(command "_insert" "blkuc1" "320,914.8" "1" "1" "0")
(command "_insert" "blkuc1" "320,914.43" "1" "1" "180")
(command "_insert" "blkuc1" "320,915.17" "1" "1" "0")
(command "_insert" "blkuc1" "320,914.8" "1" "1" "180")
(command "_insert" "blkuc1" "320,915.54" "1" "1" "0")
(command "_insert" "blkuc1" "320,915.17" "1" "1" "180")
(command "_insert" "blkuc1" "320,915.91" "1" "1" "0")
(command "_insert" "blkuc1" "320,915.54" "1" "1" "180")
(command "_insert" "blkuc1" "320,916.28" "1" "1" "0")
(command "_insert" "blkuc1" "320,915.91" "1" "1" "180")
(command "_insert" "blkuc1" "320,916.65" "1" "1" "0")
(command "_insert" "blkuc1" "320,916.28" "1" "1" "180")
(command "_insert" "blkuc1" "320,917.02" "1" "1" "0")
(command "_insert" "blkuc1" "320,916.65" "1" "1" "180")
(command "_insert" "blkuc1" "320,917.39" "1" "1" "0")
(command "_insert" "blkuc1" "320,917.02" "1" "1" "180")
(command "_insert" "blkuc1" "320,917.76" "1" "1" "0")
(command "_insert" "blkuc1" "320,917.39" "1" "1" "180")
(command "_insert" "blkuc1" "320,918.13" "1" "1" "0")
(command "_insert" "blkuc1" "320,917.76" "1" "1" "180")
(command "_insert" "blkuc1" "320,918.5" "1" "1" "0")
(command "_insert" "blkuc1" "320,918.13" "1" "1" "180")
(command "_insert" "blkuc1" "320,918.87" "1" "1" "0")
(command "_insert" "blkuc1" "320,918.5" "1" "1" "180")
(command "_insert" "blkuc1" "320,919.24" "1" "1" "0")
(command "_insert" "blkuc1" "320,918.87" "1" "1" "180")
(command "_insert" "blkuc1" "320,919.61" "1" "1" "0")
(command "_insert" "blkuc1" "320,919.24" "1" "1" "180")
(command "_insert" "blkuc1" "320,919.98" "1" "1" "0")
(command "_insert" "blkuc1" "320,919.61" "1" "1" "180")
(command "_insert" "blkuc1" "320,920.35" "1" "1" "0")
(command "_insert" "blkuc1" "320,919.98" "1" "1" "180")
(command "_insert" "blkuc1" "320,920.72" "1" "1" "0")
(command "_insert" "blkuc1" "320,920.35" "1" "1" "180")
(command "_insert" "blkuc1" "320,921.09" "1" "1" "0")
(command "_insert" "blkuc1" "320,920.72" "1" "1" "180")
(command "_insert" "blkuc1" "320,921.46" "1" "1" "0")
(command "_insert" "blkuc1" "320,921.09" "1" "1" "180")
(command "_insert" "blkuc1" "320,921.83" "1" "1" "0")
(command "_insert" "blkuc1" "320,921.46" "1" "1" "180")
(command "_insert" "blkuc1" "320,922.2" "1" "1" "0")
(command "_insert" "blkuc1" "320,921.83" "1" "1" "180")
(command "_insert" "blkuc1" "320,922.57" "1" "1" "0")
(command "_insert" "blkuc1" "320,922.2" "1" "1" "180")
(command "_insert" "blkuc1" "320,922.94" "1" "1" "0")
(command "_insert" "blkuc1" "320,922.57" "1" "1" "180")
(command "_insert" "blkuc1" "320,923.31" "1" "1" "0")
(command "_insert" "blkuc1" "320,922.94" "1" "1" "180")
(command "_insert" "blkuc1" "320,923.68" "1" "1" "0")
(command "_insert" "blkuc1" "320,923.31" "1" "1" "180")
(command "_insert" "blkuc1" "320,924.05" "1" "1" "0")
(command "_insert" "blkuc1" "320,923.68" "1" "1" "180")
(command "_insert" "blkuc1" "320,924.42" "1" "1" "0")
(command "_insert" "blkuc1" "320,924.05" "1" "1" "180")
(command "_insert" "blkuc1" "320,924.79" "1" "1" "0")
(command "_insert" "blkuc1" "320,924.42" "1" "1" "180")
(command "_insert" "blkuc1" "320,925.16" "1" "1" "0")
(command "_insert" "blkuc1" "320,924.79" "1" "1" "180")
(command "_insert" "blkuc1" "320,925.53" "1" "1" "0")
(command "_insert" "blkuc1" "320,925.16" "1" "1" "180")
(command "_insert" "blkuc1" "320,925.9" "1" "1" "0")
(command "_insert" "blkuc1" "320,925.53" "1" "1" "180")
(command "_insert" "blkuc1" "320,926.27" "1" "1" "0")
(command "_insert" "blkuc1" "320,925.9" "1" "1" "180")
(command "_insert" "blkuc1" "320,926.64" "1" "1" "0")
(command "_insert" "blkuc1" "320,926.27" "1" "1" "180")
(command "_insert" "blkuc1" "320,927.01" "1" "1" "0")
(command "_insert" "blkuc1" "320,926.64" "1" "1" "180")
(command "_insert" "blkuc1" "320,927.38" "1" "1" "0")
(command "_insert" "blkuc1" "320,927.01" "1" "1" "180")
(command "_insert" "blkuc1" "320,927.75" "1" "1" "0")
(command "_insert" "blkuc1" "320,927.38" "1" "1" "180")
(command "_layer" "set" "phccover" "")
(command "_rectangle" "318.918,933.3" "321.082,866.7")
(command "_layer" "set" "nitride" "")
(setq phc1 currobj)
(command "_layer" "set" "cover" "")
(command "_rectangle" "318.918,836.7" "321.082,963.3")
(command "_layer" "set" "nitride" "")
(command "_layer" "set" "text" "")
(command "_circle" "317.968,846.7" "0.075")
(command "_circle" "317.593,846.7" "0.15")
(command "_circle" "317.218,846.7" "0.075")
(command "_circle" "316.843,846.7" "0.15")
(command "_circle" "317.968,848.7" "0.075")
(command "_circle" "317.593,848.7" "0.075")
(command "_circle" "317.218,848.7" "0.15")
(command "_circle" "316.843,848.7" "0.15")
(command "_circle" "317.968,850.7" "0.075")
(command "_circle" "317.593,850.7" "0.15")
(command "_circle" "317.218,850.7" "0.15")
(command "_circle" "316.843,850.7" "0.15")
(command "_circle" "317.968,852.7" "0.075")
(command "_circle" "317.593,852.7" "0.075")
(command "_circle" "317.218,852.7" "0.075")
(command "_circle" "316.843,852.7" "0.075")
(command "_circle" "316.468,852.7" "0.15")
(command "_circle" "317.968,854.7" "0.075")
(command "_circle" "317.593,854.7" "0.15")
(command "_circle" "317.218,854.7" "0.075")
(command "_circle" "316.843,854.7" "0.075")
(command "_circle" "316.468,854.7" "0.15")
(command "_circle" "317.968,856.7" "0.075")
(command "_circle" "317.593,856.7" "0.075")
(command "_circle" "317.218,856.7" "0.15")
(command "_circle" "316.843,856.7" "0.075")
(command "_circle" "316.468,856.7" "0.15")
(command "_circle" "317.968,858.7" "0.075")
(command "_circle" "317.593,858.7" "0.15")
(command "_circle" "317.218,858.7" "0.15")
(command "_circle" "316.843,858.7" "0.075")
(command "_circle" "316.468,858.7" "0.15")
(command "_circle" "317.968,860.7" "0.075")
(command "_circle" "317.593,860.7" "0.075")
(command "_circle" "317.218,860.7" "0.075")
(command "_circle" "316.843,860.7" "0.15")
(command "_circle" "316.468,860.7" "0.15")
(command "_circle" "317.968,862.7" "0.075")
(command "_circle" "317.593,862.7" "0.15")
(command "_circle" "317.218,862.7" "0.075")
(command "_circle" "316.843,862.7" "0.15")
(command "_circle" "316.468,862.7" "0.15")
(command "_circle" "317.968,864.7" "0.075")
(command "_circle" "317.593,864.7" "0.075")
(command "_circle" "317.218,864.7" "0.15")
(command "_circle" "316.843,864.7" "0.15")
(command "_circle" "316.468,864.7" "0.15")
(command "_circle" "317.968,866.7" "0.075")
(command "_circle" "317.593,866.7" "0.15")
(command "_circle" "317.218,866.7" "0.15")
(command "_circle" "316.843,866.7" "0.15")
(command "_circle" "316.468,866.7" "0.15")
(command "_circle" "317.968,868.7" "0.075")
(command "_circle" "317.593,868.7" "0.075")
(command "_circle" "317.218,868.7" "0.075")
(command "_circle" "316.843,868.7" "0.075")
(command "_circle" "316.468,868.7" "0.075")
(command "_circle" "316.093,868.7" "0.15")
(command "_circle" "317.968,870.7" "0.075")
(command "_circle" "317.593,870.7" "0.15")
(command "_circle" "317.218,870.7" "0.075")
(command "_circle" "316.843,870.7" "0.075")
(command "_circle" "316.468,870.7" "0.075")
(command "_circle" "316.093,870.7" "0.15")
(command "_circle" "317.968,872.7" "0.075")
(command "_circle" "317.593,872.7" "0.075")
(command "_circle" "317.218,872.7" "0.15")
(command "_circle" "316.843,872.7" "0.075")
(command "_circle" "316.468,872.7" "0.075")
(command "_circle" "316.093,872.7" "0.15")
(command "_circle" "317.968,874.7" "0.075")
(command "_circle" "317.593,874.7" "0.15")
(command "_circle" "317.218,874.7" "0.15")
(command "_circle" "316.843,874.7" "0.075")
(command "_circle" "316.468,874.7" "0.075")
(command "_circle" "316.093,874.7" "0.15")
(command "_circle" "317.968,876.7" "0.075")
(command "_circle" "317.593,876.7" "0.075")
(command "_circle" "317.218,876.7" "0.075")
(command "_circle" "316.843,876.7" "0.15")
(command "_circle" "316.468,876.7" "0.075")
(command "_circle" "316.093,876.7" "0.15")
(command "_circle" "317.968,878.7" "0.075")
(command "_circle" "317.593,878.7" "0.15")
(command "_circle" "317.218,878.7" "0.075")
(command "_circle" "316.843,878.7" "0.15")
(command "_circle" "316.468,878.7" "0.075")
(command "_circle" "316.093,878.7" "0.15")
(command "_circle" "317.968,880.7" "0.075")
(command "_circle" "317.593,880.7" "0.075")
(command "_circle" "317.218,880.7" "0.15")
(command "_circle" "316.843,880.7" "0.15")
(command "_circle" "316.468,880.7" "0.075")
(command "_circle" "316.093,880.7" "0.15")
(command "_circle" "317.968,882.7" "0.075")
(command "_circle" "317.593,882.7" "0.15")
(command "_circle" "317.218,882.7" "0.15")
(command "_circle" "316.843,882.7" "0.15")
(command "_circle" "316.468,882.7" "0.075")
(command "_circle" "316.093,882.7" "0.15")
(command "_circle" "317.968,884.7" "0.075")
(command "_circle" "317.593,884.7" "0.075")
(command "_circle" "317.218,884.7" "0.075")
(command "_circle" "316.843,884.7" "0.075")
(command "_circle" "316.468,884.7" "0.15")
(command "_circle" "316.093,884.7" "0.15")
(command "_circle" "317.968,886.7" "0.075")
(command "_circle" "317.593,886.7" "0.15")
(command "_circle" "317.218,886.7" "0.075")
(command "_circle" "316.843,886.7" "0.075")
(command "_circle" "316.468,886.7" "0.15")
(command "_circle" "316.093,886.7" "0.15")
(command "_circle" "317.968,888.7" "0.075")
(command "_circle" "317.593,888.7" "0.075")
(command "_circle" "317.218,888.7" "0.15")
(command "_circle" "316.843,888.7" "0.075")
(command "_circle" "316.468,888.7" "0.15")
(command "_circle" "316.093,888.7" "0.15")
(command "_circle" "317.968,890.7" "0.075")
(command "_circle" "317.593,890.7" "0.15")
(command "_circle" "317.218,890.7" "0.15")
(command "_circle" "316.843,890.7" "0.075")
(command "_circle" "316.468,890.7" "0.15")
(command "_circle" "316.093,890.7" "0.15")
(command "_circle" "317.968,892.7" "0.075")
(command "_circle" "317.593,892.7" "0.075")
(command "_circle" "317.218,892.7" "0.075")
(command "_circle" "316.843,892.7" "0.15")
(command "_circle" "316.468,892.7" "0.15")
(command "_circle" "316.093,892.7" "0.15")
(command "_circle" "317.968,894.7" "0.075")
(command "_circle" "317.593,894.7" "0.15")
(command "_circle" "317.218,894.7" "0.075")
(command "_circle" "316.843,894.7" "0.15")
(command "_circle" "316.468,894.7" "0.15")
(command "_circle" "316.093,894.7" "0.15")
(command "_circle" "317.968,896.7" "0.075")
(command "_circle" "317.593,896.7" "0.075")
(command "_circle" "317.218,896.7" "0.15")
(command "_circle" "316.843,896.7" "0.15")
(command "_circle" "316.468,896.7" "0.15")
(command "_circle" "316.093,896.7" "0.15")
(command "_circle" "317.968,898.7" "0.075")
(command "_circle" "317.593,898.7" "0.15")
(command "_circle" "317.218,898.7" "0.15")
(command "_circle" "316.843,898.7" "0.15")
(command "_circle" "316.468,898.7" "0.15")
(command "_circle" "316.093,898.7" "0.15")
(command "_circle" "317.968,900.7" "0.075")
(command "_circle" "317.593,900.7" "0.075")
(command "_circle" "317.218,900.7" "0.075")
(command "_circle" "316.843,900.7" "0.075")
(command "_circle" "316.468,900.7" "0.075")
(command "_circle" "316.093,900.7" "0.075")
(command "_circle" "315.718,900.7" "0.15")
(command "_circle" "317.968,902.7" "0.075")
(command "_circle" "317.593,902.7" "0.15")
(command "_circle" "317.218,902.7" "0.075")
(command "_circle" "316.843,902.7" "0.075")
(command "_circle" "316.468,902.7" "0.075")
(command "_circle" "316.093,902.7" "0.075")
(command "_circle" "315.718,902.7" "0.15")
(command "_circle" "317.968,904.7" "0.075")
(command "_circle" "317.593,904.7" "0.075")
(command "_circle" "317.218,904.7" "0.15")
(command "_circle" "316.843,904.7" "0.075")
(command "_circle" "316.468,904.7" "0.075")
(command "_circle" "316.093,904.7" "0.075")
(command "_circle" "315.718,904.7" "0.15")
(command "_circle" "317.968,906.7" "0.075")
(command "_circle" "317.593,906.7" "0.15")
(command "_circle" "317.218,906.7" "0.15")
(command "_circle" "316.843,906.7" "0.075")
(command "_circle" "316.468,906.7" "0.075")
(command "_circle" "316.093,906.7" "0.075")
(command "_circle" "315.718,906.7" "0.15")
(command "_circle" "317.968,908.7" "0.075")
(command "_circle" "317.593,908.7" "0.075")
(command "_circle" "317.218,908.7" "0.075")
(command "_circle" "316.843,908.7" "0.15")
(command "_circle" "316.468,908.7" "0.075")
(command "_circle" "316.093,908.7" "0.075")
(command "_circle" "315.718,908.7" "0.15")
(command "_circle" "317.968,910.7" "0.075")
(command "_circle" "317.593,910.7" "0.15")
(command "_circle" "317.218,910.7" "0.075")
(command "_circle" "316.843,910.7" "0.15")
(command "_circle" "316.468,910.7" "0.075")
(command "_circle" "316.093,910.7" "0.075")
(command "_circle" "315.718,910.7" "0.15")
(command "_circle" "317.968,912.7" "0.075")
(command "_circle" "317.593,912.7" "0.075")
(command "_circle" "317.218,912.7" "0.15")
(command "_circle" "316.843,912.7" "0.15")
(command "_circle" "316.468,912.7" "0.075")
(command "_circle" "316.093,912.7" "0.075")
(command "_circle" "315.718,912.7" "0.15")
(command "_circle" "317.968,914.7" "0.075")
(command "_circle" "317.593,914.7" "0.15")
(command "_circle" "317.218,914.7" "0.15")
(command "_circle" "316.843,914.7" "0.15")
(command "_circle" "316.468,914.7" "0.075")
(command "_circle" "316.093,914.7" "0.075")
(command "_circle" "315.718,914.7" "0.15")
(command "_circle" "317.968,916.7" "0.075")
(command "_circle" "317.593,916.7" "0.075")
(command "_circle" "317.218,916.7" "0.075")
(command "_circle" "316.843,916.7" "0.075")
(command "_circle" "316.468,916.7" "0.15")
(command "_circle" "316.093,916.7" "0.075")
(command "_circle" "315.718,916.7" "0.15")
(command "_circle" "317.968,918.7" "0.075")
(command "_circle" "317.593,918.7" "0.15")
(command "_circle" "317.218,918.7" "0.075")
(command "_circle" "316.843,918.7" "0.075")
(command "_circle" "316.468,918.7" "0.15")
(command "_circle" "316.093,918.7" "0.075")
(command "_circle" "315.718,918.7" "0.15")
(command "_circle" "317.968,920.7" "0.075")
(command "_circle" "317.593,920.7" "0.075")
(command "_circle" "317.218,920.7" "0.15")
(command "_circle" "316.843,920.7" "0.075")
(command "_circle" "316.468,920.7" "0.15")
(command "_circle" "316.093,920.7" "0.075")
(command "_circle" "315.718,920.7" "0.15")
(command "_circle" "317.968,922.7" "0.075")
(command "_circle" "317.593,922.7" "0.15")
(command "_circle" "317.218,922.7" "0.15")
(command "_circle" "316.843,922.7" "0.075")
(command "_circle" "316.468,922.7" "0.15")
(command "_circle" "316.093,922.7" "0.075")
(command "_circle" "315.718,922.7" "0.15")
(command "_circle" "317.968,924.7" "0.075")
(command "_circle" "317.593,924.7" "0.075")
(command "_circle" "317.218,924.7" "0.075")
(command "_circle" "316.843,924.7" "0.15")
(command "_circle" "316.468,924.7" "0.15")
(command "_circle" "316.093,924.7" "0.075")
(command "_circle" "315.718,924.7" "0.15")
(command "_circle" "317.968,926.7" "0.075")
(command "_circle" "317.593,926.7" "0.15")
(command "_circle" "317.218,926.7" "0.075")
(command "_circle" "316.843,926.7" "0.15")
(command "_circle" "316.468,926.7" "0.15")
(command "_circle" "316.093,926.7" "0.075")
(command "_circle" "315.718,926.7" "0.15")
(command "_circle" "317.968,928.7" "0.075")
(command "_circle" "317.593,928.7" "0.075")
(command "_circle" "317.218,928.7" "0.15")
(command "_circle" "316.843,928.7" "0.15")
(command "_circle" "316.468,928.7" "0.15")
(command "_circle" "316.093,928.7" "0.075")
(command "_circle" "315.718,928.7" "0.15")
(command "_circle" "317.968,930.7" "0.075")
(command "_circle" "317.593,930.7" "0.15")
(command "_circle" "317.218,930.7" "0.15")
(command "_circle" "316.843,930.7" "0.15")
(command "_circle" "316.468,930.7" "0.15")
(command "_circle" "316.093,930.7" "0.075")
(command "_circle" "315.718,930.7" "0.15")
(command "_circle" "317.968,932.7" "0.075")
(command "_circle" "317.593,932.7" "0.075")
(command "_circle" "317.218,932.7" "0.075")
(command "_circle" "316.843,932.7" "0.075")
(command "_circle" "316.468,932.7" "0.075")
(command "_circle" "316.093,932.7" "0.15")
(command "_circle" "315.718,932.7" "0.15")
(command "_circle" "317.968,934.7" "0.075")
(command "_circle" "317.593,934.7" "0.15")
(command "_circle" "317.218,934.7" "0.075")
(command "_circle" "316.843,934.7" "0.075")
(command "_circle" "316.468,934.7" "0.075")
(command "_circle" "316.093,934.7" "0.15")
(command "_circle" "315.718,934.7" "0.15")
(command "_circle" "317.968,936.7" "0.075")
(command "_circle" "317.593,936.7" "0.075")
(command "_circle" "317.218,936.7" "0.15")
(command "_circle" "316.843,936.7" "0.075")
(command "_circle" "316.468,936.7" "0.075")
(command "_circle" "316.093,936.7" "0.15")
(command "_circle" "315.718,936.7" "0.15")
(command "_circle" "317.968,938.7" "0.075")
(command "_circle" "317.593,938.7" "0.15")
(command "_circle" "317.218,938.7" "0.15")
(command "_circle" "316.843,938.7" "0.075")
(command "_circle" "316.468,938.7" "0.075")
(command "_circle" "316.093,938.7" "0.15")
(command "_circle" "315.718,938.7" "0.15")
(command "_circle" "317.968,940.7" "0.075")
(command "_circle" "317.593,940.7" "0.075")
(command "_circle" "317.218,940.7" "0.075")
(command "_circle" "316.843,940.7" "0.15")
(command "_circle" "316.468,940.7" "0.075")
(command "_circle" "316.093,940.7" "0.15")
(command "_circle" "315.718,940.7" "0.15")
(command "_circle" "317.968,942.7" "0.075")
(command "_circle" "317.593,942.7" "0.15")
(command "_circle" "317.218,942.7" "0.075")
(command "_circle" "316.843,942.7" "0.15")
(command "_circle" "316.468,942.7" "0.075")
(command "_circle" "316.093,942.7" "0.15")
(command "_circle" "315.718,942.7" "0.15")
(command "_circle" "317.968,944.7" "0.075")
(command "_circle" "317.593,944.7" "0.075")
(command "_circle" "317.218,944.7" "0.15")
(command "_circle" "316.843,944.7" "0.15")
(command "_circle" "316.468,944.7" "0.075")
(command "_circle" "316.093,944.7" "0.15")
(command "_circle" "315.718,944.7" "0.15")
(command "_circle" "317.968,946.7" "0.075")
(command "_circle" "317.593,946.7" "0.15")
(command "_circle" "317.218,946.7" "0.15")
(command "_circle" "316.843,946.7" "0.15")
(command "_circle" "316.468,946.7" "0.075")
(command "_circle" "316.093,946.7" "0.15")
(command "_circle" "315.718,946.7" "0.15")
(command "_circle" "317.968,948.7" "0.075")
(command "_circle" "317.593,948.7" "0.075")
(command "_circle" "317.218,948.7" "0.075")
(command "_circle" "316.843,948.7" "0.075")
(command "_circle" "316.468,948.7" "0.15")
(command "_circle" "316.093,948.7" "0.15")
(command "_circle" "315.718,948.7" "0.15")
(command "_circle" "317.968,950.7" "0.075")
(command "_circle" "317.593,950.7" "0.15")
(command "_circle" "317.218,950.7" "0.075")
(command "_circle" "316.843,950.7" "0.075")
(command "_circle" "316.468,950.7" "0.15")
(command "_circle" "316.093,950.7" "0.15")
(command "_circle" "315.718,950.7" "0.15")
(command "_circle" "317.968,952.7" "0.075")
(command "_circle" "317.593,952.7" "0.075")
(command "_circle" "317.218,952.7" "0.15")
(command "_circle" "316.843,952.7" "0.075")
(command "_circle" "316.468,952.7" "0.15")
(command "_circle" "316.093,952.7" "0.15")
(command "_circle" "315.718,952.7" "0.15")
(command "_circle" "317.968,954.7" "0.075")
(command "_circle" "317.593,954.7" "0.15")
(command "_circle" "317.218,954.7" "0.15")
(command "_circle" "316.843,954.7" "0.075")
(command "_circle" "316.468,954.7" "0.15")
(command "_circle" "316.093,954.7" "0.15")
(command "_circle" "315.718,954.7" "0.15")
(command "_circle" "317.968,956.7" "0.075")
(command "_circle" "317.593,956.7" "0.075")
(command "_circle" "317.218,956.7" "0.075")
(command "_circle" "316.843,956.7" "0.15")
(command "_circle" "316.468,956.7" "0.15")
(command "_circle" "316.093,956.7" "0.15")
(command "_circle" "315.718,956.7" "0.15")
(command "_circle" "317.968,958.7" "0.075")
(command "_circle" "317.593,958.7" "0.15")
(command "_circle" "317.218,958.7" "0.075")
(command "_circle" "316.843,958.7" "0.15")
(command "_circle" "316.468,958.7" "0.15")
(command "_circle" "316.093,958.7" "0.15")
(command "_circle" "315.718,958.7" "0.15")
(command "_circle" "317.968,960.7" "0.075")
(command "_circle" "317.593,960.7" "0.075")
(command "_circle" "317.218,960.7" "0.15")
(command "_circle" "316.843,960.7" "0.15")
(command "_circle" "316.468,960.7" "0.15")
(command "_circle" "316.093,960.7" "0.15")
(command "_circle" "315.718,960.7" "0.15")
(command "_circle" "317.968,962.7" "0.075")
(command "_circle" "317.593,962.7" "0.15")
(command "_circle" "317.218,962.7" "0.15")
(command "_circle" "316.843,962.7" "0.15")
(command "_circle" "316.468,962.7" "0.15")
(command "_circle" "316.093,962.7" "0.15")
(command "_circle" "315.718,962.7" "0.15")
(command "_layer" "set" "nitride" "")
(command "_layer" "set" "text" "")
(command-s "_text" "306.918,963.3" "2" "-90" "a = 370 nm" )
(sssetfirst nil (ssget "_L"))
(if (not (numberp (vl-string-search "Mac" (getvar "platform")))) (c:txtexp))
(command "_layer" "set" "nitride" "")
(command "_layer" "set" "text" "")
(command-s "_text" "303.918,963.3" "2" "-90" "gap = 250 nm" )
(sssetfirst nil (ssget "_L"))
(if (not (numberp (vl-string-search "Mac" (getvar "platform")))) (c:txtexp))
(command "_layer" "set" "nitride" "")
(command "_layer" "set" "text" "")
(command-s "_text" "300.918,963.3" "2" "-90" "amplitude = 127 nm" )
(sssetfirst nil (ssget "_L"))
(if (not (numberp (vl-string-search "Mac" (getvar "platform")))) (c:txtexp))
(command "_layer" "set" "nitride" "")
(command "_layer" "set" "text" "")
(command-s "_text" "297.918,963.3" "2" "-90" "start width = 280 nm" )
(sssetfirst nil (ssget "_L"))
(if (not (numberp (vl-string-search "Mac" (getvar "platform")))) (c:txtexp))
(command "_layer" "set" "nitride" "")
(command "_layer" "set" "text" "")
(command-s "_text" "294.918,963.3" "2" "-90" "width = 289 nm" )
(sssetfirst nil (ssget "_L"))
(if (not (numberp (vl-string-search "Mac" (getvar "platform")))) (c:txtexp))
(command "_layer" "set" "nitride" "")
(command "_layer" "set" "text" "")
(command-s "_text" "291.918,963.3" "2" "-90" "taper: 15" )
(sssetfirst nil (ssget "_L"))
(if (not (numberp (vl-string-search "Mac" (getvar "platform")))) (c:txtexp))
(command "_layer" "set" "nitride" "")
(command "_layer" "set" "text" "")
(command-s "_text" "288.918,963.3" "2" "-90" "nominal: 150" )
(sssetfirst nil (ssget "_L"))
(if (not (numberp (vl-string-search "Mac" (getvar "platform")))) (c:txtexp))
(command "_layer" "set" "nitride" "")
(command "_layer" "set" "indicators" "")
(setq coords (list 
(list 240.415 940) 
(list 240.415 920) 
(list 220.415 900) 
(list 240.415 880) 
(list 240.415 860) 
(list 240.415 900) 
(list 240.415 887.0711) 
(list 227.4861 900) 
(list 240.415 912.9289) 
(list 240.415 900)))
(apply 'command (append '("pline") coords '("c")))
(command "._fillet" "radius" "1" "._fillet" "P" (entlast))
(setq coords (list 
(list 399.585 940) 
(list 399.585 920) 
(list 419.585 900) 
(list 399.585 880) 
(list 399.585 860) 
(list 399.585 900) 
(list 399.585 887.0711) 
(list 412.5139 900) 
(list 399.585 912.9289) 
(list 399.585 900)))
(apply 'command (append '("pline") coords '("c")))
(command "._fillet" "radius" "1" "._fillet" "P" (entlast))
(command "_layer" "set" "holes" "")
(command "_circle" "238.0629,914.1124" "0.5")
(command "_circle" "235.7109,911.7603" "0.5")
(command "_circle" "233.3588,909.4083" "0.5")
(command "_circle" "231.0067,907.0562" "0.5")
(command "_circle" "228.6547,904.7041" "0.5")
(command "_circle" "226.3026,902.3521" "0.5")
(command "_circle" "223.9505,900" "0.5")
(command "_circle" "226.3026,897.6479" "0.5")
(command "_circle" "228.6547,895.2959" "0.5")
(command "_circle" "231.0067,892.9438" "0.5")
(command "_circle" "233.3588,890.5917" "0.5")
(command "_circle" "235.7109,888.2397" "0.5")
(command "_circle" "238.0629,885.8876" "0.5")
(command "_circle" "401.9371,914.1124" "0.5")
(command "_circle" "404.2891,911.7603" "0.5")
(command "_circle" "406.6412,909.4083" "0.5")
(command "_circle" "408.9933,907.0562" "0.5")
(command "_circle" "411.3453,904.7041" "0.5")
(command "_circle" "413.6974,902.3521" "0.5")
(command "_circle" "416.0495,900" "0.5")
(command "_circle" "413.6974,897.6479" "0.5")
(command "_circle" "411.3453,895.2959" "0.5")
(command "_circle" "408.9933,892.9438" "0.5")
(command "_circle" "406.6412,890.5917" "0.5")
(command "_circle" "404.2891,888.2397" "0.5")
(command "_circle" "401.9371,885.8876" "0.5")
(command "_layer" "set" "nitride" "")
(command "_block" "blkcoupler1" "320,900" coupler1 "")
(command "_insert" "blkcoupler1" "320,900" "1" "1" "0")
(command "_insert" "blkcoupler1" "320,900" "1" "1" "180")
(command "_block" "blksinglenanobeam1" "320,900" singlenanobeam1 "")
(command "_insert" "blksinglenanobeam1" "320,900" "1" "1" "0")
(command "_insert" "blksinglenanobeam1" "320,900" "1" "1" "180")
(command "_block" "blkanglednodearray1" "320,900" anglednodearray1 "")
(command "_insert" "blkanglednodearray1" "320,900" "1" "1" "0")
(command "_insert" "blkanglednodearray1" "320,900" "1" "1" "180")
(command "_block" "blkcooledsinglenanobeam1" "320,900" cooledsinglenanobeam1 "")
(command "_insert" "blkcooledsinglenanobeam1" "320,900" "1" "1" "0")
(command "_insert" "blkcooledsinglenanobeam1" "320,900" "1" "1" "180")
(command "_block" "blkyjunction1" "320,900" yjunction1 "")
(command "_insert" "blkyjunction1" "320,900" "1" "1" "0")
(command "_insert" "blkyjunction1" "320,900" "1" "1" "180")
; DRAWING BULGING VEE GROOVE
(command "_layer" "set" "vgroove" "")
(setq coords (list 
(list 245.415 -605) 
(list 245.415 0) 
(list 245.415 0) 
(list 245.415 1800) 
(list 245.415 1800) 
(list 245.415 2405) 
(list 394.585 2405) 
(list 394.585 1800) 
(list 394.585 1800) 
(list 394.585 0) 
(list 394.585 0) 
(list 394.585 -605)))
(apply 'command (append '("pline") coords '("c")))
(command "._fillet" "radius" "0" "._fillet" "P" (entlast))
(command "_layer" "set" "window" "")
(command "_rectangle" "245.415,-1935" "394.585,-600")
(command "_rectangle" "245.415,2400" "394.585,5300")
(command "_layer" "set" "grid" "")
(command "_rectangle" "246.415,-1934" "269.9433,-1909.2133")
(command "_array" "last" "" "R" "75" "3" "25.7867" "24.5283")
(command "_rectangle" "321,-1934" "344.5283,-1909.2133")
(command "_array" "last" "" "R" "75" "3" "25.7867" "24.5283")
(command "_rectangle" "246.415,1" "269.9433,25.7")
(command "_array" "last" "" "R" "70" "3" "25.7" "24.5283")
(command "_rectangle" "321,1" "344.5283,25.7")
(command "_array" "last" "" "R" "70" "3" "25.7" "24.5283")
(command "_rectangle" "246.415,1801" "269.9433,1825.9185")
(command "_array" "last" "" "R" "135" "3" "25.9185" "24.5283")
(command "_rectangle" "321,1801" "344.5283,1825.9185")
(command "_array" "last" "" "R" "135" "3" "25.9185" "24.5283")
(command "_layer" "set" "vgrooveFDA" "")
(command "_rectangle" "394.585,-2233" "245.415,-1933")
(command "_layer" "set" "nitride" "")
(command "_layer" "set" "holes" "")
(command "_circle" "397.085,331.5" "0.5")
(command "_array" "last" "" "R" "379" "1" "3" "2.5")
(command "_circle" "242.915,331.5" "0.5")
(command "_array" "last" "" "R" "379" "1" "3" "-2.5")
(command "_layer" "set" "nitride" "")
(command "_layer" "set" "window" "")
(command "_layer" "set" "window" "")
(command "_rectangle" "240.415,0" "-986.225,1800")
(command "._fillet" "radius" "20" "._fillet" "P" (entlast))
(command "_layer" "set" "grid" "")
(command "_rectangle" "-985.225,1" "-960.6908,25.7")
(command "_array" "last" "" "R" "70" "48" "25.7" "25.5342")
(command "_layer" "set" "window" "")
(command "_rectangle" "399.585,0" "560.415,1800")
(command "._fillet" "radius" "20" "._fillet" "P" (entlast))
(command "_layer" "set" "grid" "")
(command "_rectangle" "400.585,1" "422.4179,25.7")
(command "_array" "last" "" "R" "70" "7" "25.7" "22.8329")
(command "_layer" "set" "nitride" "")
; DRAWING REGION LAYER
(command "_layer" "set" "regionLayer1" "")
(command "_rectangle" "240,-460" "400,2260")
(command "_layer" "set" "nitride" "")
(setq coupler1 nil)
(setq singlenanobeam1 nil)
(setq anglednodearray1 nil)
(setq cooledsinglenanobeam1 nil)
(setq yjunction1 nil)
; DEVICE #2
(command "_layer" "set" "window" "")
(command "_circle" "552.915,-415" "5")
(command "_circle" "552.915,-402.5" "5")
(command "_layer" "set" "nitride" "")
(setq currobj nil)
(setq currobj (ssadd))
; DRAWING COUPLER
(setq coords (list 
(list 640.0555 -415) 
(list 640.0555 -413) 
(list 713.585 -413) 
(list 713.585 -413) 
(list 713.9677 -413.0761) 
(list 714.2921 -413.2929) 
(list 714.5089 -413.6173) 
(list 714.585 -414) 
(list 714.585 -411.8) 
(list 714.585 -411.8) 
(list 714.5089 -412.1827) 
(list 714.2921 -412.5071) 
(list 713.9677 -412.7239) 
(list 713.585 -412.8) 
(list 640.0555 -412.8) 
(list 640.0555 -410.8) 
(list 639.9445 -410.8) 
(list 639.9445 -412.8) 
(list 566.415 -412.8) 
(list 566.0323 -412.7239) 
(list 565.7079 -412.5071) 
(list 565.4911 -412.1827) 
(list 565.415 -411.8) 
(list 565.415 -411.8) 
(list 565.415 -414) 
(list 565.4911 -413.6173) 
(list 565.7079 -413.2929) 
(list 566.0323 -413.0761) 
(list 566.415 -413) 
(list 566.415 -413) 
(list 639.9445 -413) 
(list 639.9445 -415)))
(apply 'command (append '("pline") coords '("c")))
(setq currobj (ssadd (entlast) currobj))
(command "._fillet" "radius" "0.3" "._fillet" "P" (entlast))
(command "_layer" "set" "holes" "")
(command "_circle" "640,-412.9" "0.113")
(setq currobj (ssadd (entlast) currobj))
(command "_layer" "set" "nitride" "")
(command "_layer" "set" "text" "")
(command "_circle" "639.2,-415" "0.075")
(command "_circle" "639.2,-414.7" "0.075")
(command "_circle" "639.2,-414.4" "0.075")
(command "_circle" "638.9,-415" "0.075")
(command "_circle" "638.9,-414.7" "0.075")
(command "_circle" "638.9,-414.4" "0.075")
(command "_circle" "638.6,-415" "0.075")
(command "_circle" "638.6,-414.7" "0.075")
(command "_circle" "638.6,-414.4" "0.075")
(command "_layer" "set" "nitride" "")
(command "_layer" "set" "prebias" "")
(command "_rectangle" "565.415,-414" "714.585,-411.8")
(setq currobj (ssadd (entlast) currobj))
(command "_rectangle" "639.9445,-415" "640.0555,-410.8")
(setq currobj (ssadd (entlast) currobj))
(command "_layer" "set" "nitride" "")
(setq coupler2 currobj)
(setq currobj nil)
(setq currobj (ssadd))
; DRAWING SINGLE NANOBEAM
(setq coords (list 
(list 640.0555 -410.8) 
(list 640.0555 -409.1417) 
(list 640.0555 -407.4833) 
(list 640.0555 -405.825) 
(list 640.0555 -404.1667) 
(list 640.0555 -402.5083) 
(list 640.0555 -400.85) 
(list 640.0555 -399.1917) 
(list 640.0555 -397.5333) 
(list 640.0556 -395.875) 
(list 640.0556 -394.2167) 
(list 640.0556 -392.5583) 
(list 640.0556 -390.9) 
(list 640.0557 -389.2417) 
(list 640.0557 -387.5833) 
(list 640.0558 -385.925) 
(list 640.0558 -384.2667) 
(list 640.0559 -382.6083) 
(list 640.0559 -380.95) 
(list 640.056 -379.2917) 
(list 640.0561 -377.6333) 
(list 640.0562 -375.975) 
(list 640.0563 -374.3167) 
(list 640.0564 -372.6583) 
(list 640.0565 -371) 
(list 640.0567 -369.3417) 
(list 640.0568 -367.6833) 
(list 640.057 -366.025) 
(list 640.0571 -364.3667) 
(list 640.0573 -362.7083) 
(list 640.0575 -361.05) 
(list 640.0577 -359.3917) 
(list 640.058 -357.7333) 
(list 640.0582 -356.075) 
(list 640.0584 -354.4167) 
(list 640.0587 -352.7583) 
(list 640.059 -351.1) 
(list 640.0593 -349.4417) 
(list 640.0596 -347.7833) 
(list 640.0599 -346.125) 
(list 640.0603 -344.4667) 
(list 640.0607 -342.8083) 
(list 640.0611 -341.15) 
(list 640.0615 -339.4917) 
(list 640.0619 -337.8333) 
(list 640.0623 -336.175) 
(list 640.0628 -334.5167) 
(list 640.0633 -332.8583) 
(list 640.0638 -331.2) 
(list 640.0643 -329.5417) 
(list 640.0649 -327.8833) 
(list 640.0654 -326.225) 
(list 640.066 -324.5667) 
(list 640.0667 -322.9083) 
(list 640.0673 -321.25) 
(list 640.068 -319.5917) 
(list 640.0687 -317.9333) 
(list 640.0694 -316.275) 
(list 640.0701 -314.6167) 
(list 640.0709 -312.9583) 
(list 640.0717 -311.3) 
(list 640.0725 -309.6417) 
(list 640.0734 -307.9833) 
(list 640.0742 -306.325) 
(list 640.0751 -304.6667) 
(list 640.0761 -303.0083) 
(list 640.077 -301.35) 
(list 640.078 -299.6917) 
(list 640.0791 -298.0333) 
(list 640.0801 -296.375) 
(list 640.0812 -294.7167) 
(list 640.0823 -293.0583) 
(list 640.0835 -291.4) 
(list 640.0847 -289.7417) 
(list 640.0859 -288.0833) 
(list 640.0871 -286.425) 
(list 640.0884 -284.7667) 
(list 640.0897 -283.1083) 
(list 640.0911 -281.45) 
(list 640.0924 -279.7917) 
(list 640.0939 -278.1333) 
(list 640.0953 -276.475) 
(list 640.0968 -274.8167) 
(list 640.0984 -273.1583) 
(list 640.0999 -271.5) 
(list 640.1015 -269.8417) 
(list 640.1032 -268.1833) 
(list 640.1049 -266.525) 
(list 640.1066 -264.8667) 
(list 640.1083 -263.2083) 
(list 640.1101 -261.55) 
(list 640.112 -259.8917) 
(list 640.1139 -258.2333) 
(list 640.1158 -256.575) 
(list 640.1177 -254.9167) 
(list 640.1198 -253.2583) 
(list 640.1218 -251.6) 
(list 640.1239 -249.9417) 
(list 640.126 -248.2833) 
(list 640.1282 -246.625) 
(list 640.1304 -244.9667) 
(list 640.1327 -243.3083) 
(list 640.135 -241.65) 
(list 640.1374 -239.9917) 
(list 640.1398 -238.3333) 
(list 640.1423 -236.675) 
(list 640.1448 -235.0167) 
(list 640.1473 -233.3583) 
(list 640.1499 -231.7) 
(list 640.1526 -230.0417) 
(list 640.1552 -228.3833) 
(list 640.158 -226.725) 
(list 640.1608 -225.0667) 
(list 640.1636 -223.4083) 
(list 640.1665 -221.75) 
(list 640.1695 -220.0917) 
(list 640.1725 -218.4333) 
(list 640.1755 -216.775) 
(list 640.1786 -215.1167) 
(list 640.1818 -213.4583) 
(list 640.185 -211.8) 
(list 639.815 -211.8) 
(list 639.8182 -213.4583) 
(list 639.8214 -215.1167) 
(list 639.8245 -216.775) 
(list 639.8275 -218.4333) 
(list 639.8305 -220.0917) 
(list 639.8335 -221.75) 
(list 639.8364 -223.4083) 
(list 639.8392 -225.0667) 
(list 639.842 -226.725) 
(list 639.8448 -228.3833) 
(list 639.8474 -230.0417) 
(list 639.8501 -231.7) 
(list 639.8527 -233.3583) 
(list 639.8552 -235.0167) 
(list 639.8577 -236.675) 
(list 639.8602 -238.3333) 
(list 639.8626 -239.9917) 
(list 639.865 -241.65) 
(list 639.8673 -243.3083) 
(list 639.8696 -244.9667) 
(list 639.8718 -246.625) 
(list 639.874 -248.2833) 
(list 639.8761 -249.9417) 
(list 639.8782 -251.6) 
(list 639.8802 -253.2583) 
(list 639.8823 -254.9167) 
(list 639.8842 -256.575) 
(list 639.8861 -258.2333) 
(list 639.888 -259.8917) 
(list 639.8899 -261.55) 
(list 639.8917 -263.2083) 
(list 639.8934 -264.8667) 
(list 639.8951 -266.525) 
(list 639.8968 -268.1833) 
(list 639.8985 -269.8417) 
(list 639.9001 -271.5) 
(list 639.9016 -273.1583) 
(list 639.9032 -274.8167) 
(list 639.9047 -276.475) 
(list 639.9061 -278.1333) 
(list 639.9076 -279.7917) 
(list 639.9089 -281.45) 
(list 639.9103 -283.1083) 
(list 639.9116 -284.7667) 
(list 639.9129 -286.425) 
(list 639.9141 -288.0833) 
(list 639.9153 -289.7417) 
(list 639.9165 -291.4) 
(list 639.9177 -293.0583) 
(list 639.9188 -294.7167) 
(list 639.9199 -296.375) 
(list 639.9209 -298.0333) 
(list 639.922 -299.6917) 
(list 639.923 -301.35) 
(list 639.9239 -303.0083) 
(list 639.9249 -304.6667) 
(list 639.9258 -306.325) 
(list 639.9266 -307.9833) 
(list 639.9275 -309.6417) 
(list 639.9283 -311.3) 
(list 639.9291 -312.9583) 
(list 639.9299 -314.6167) 
(list 639.9306 -316.275) 
(list 639.9313 -317.9333) 
(list 639.932 -319.5917) 
(list 639.9327 -321.25) 
(list 639.9333 -322.9083) 
(list 639.934 -324.5667) 
(list 639.9346 -326.225) 
(list 639.9351 -327.8833) 
(list 639.9357 -329.5417) 
(list 639.9362 -331.2) 
(list 639.9367 -332.8583) 
(list 639.9372 -334.5167) 
(list 639.9377 -336.175) 
(list 639.9381 -337.8333) 
(list 639.9385 -339.4917) 
(list 639.9389 -341.15) 
(list 639.9393 -342.8083) 
(list 639.9397 -344.4667) 
(list 639.9401 -346.125) 
(list 639.9404 -347.7833) 
(list 639.9407 -349.4417) 
(list 639.941 -351.1) 
(list 639.9413 -352.7583) 
(list 639.9416 -354.4167) 
(list 639.9418 -356.075) 
(list 639.942 -357.7333) 
(list 639.9423 -359.3917) 
(list 639.9425 -361.05) 
(list 639.9427 -362.7083) 
(list 639.9429 -364.3667) 
(list 639.943 -366.025) 
(list 639.9432 -367.6833) 
(list 639.9433 -369.3417) 
(list 639.9435 -371) 
(list 639.9436 -372.6583) 
(list 639.9437 -374.3167) 
(list 639.9438 -375.975) 
(list 639.9439 -377.6333) 
(list 639.944 -379.2917) 
(list 639.9441 -380.95) 
(list 639.9441 -382.6083) 
(list 639.9442 -384.2667) 
(list 639.9442 -385.925) 
(list 639.9443 -387.5833) 
(list 639.9443 -389.2417) 
(list 639.9444 -390.9) 
(list 639.9444 -392.5583) 
(list 639.9444 -394.2167) 
(list 639.9444 -395.875) 
(list 639.9445 -397.5333) 
(list 639.9445 -399.1917) 
(list 639.9445 -400.85) 
(list 639.9445 -402.5083) 
(list 639.9445 -404.1667) 
(list 639.9445 -405.825) 
(list 639.9445 -407.4833) 
(list 639.9445 -409.1417) 
(list 639.9445 -410.8)))
(apply 'command (append '("pline") coords '("c")))
(setq currobj (ssadd (entlast) currobj))
(command "_layer" "set" "prebias" "")
(command "_rectangle" "639.815,-410.8" "640.185,-211.8")
(setq currobj (ssadd (entlast) currobj))
(command "_layer" "set" "nitride" "")
(setq singlenanobeam2 currobj)
(setq currobj nil)
(setq currobj (ssadd))
; DRAWING NODE ARRAY
(setq coords (list 
(list 640.185 -211.8) 
(list 640.5625 -201.8) 
(list 640.5625 -201.8) 
(list 640.5625 -200.8) 
(list 714.585 -212.6864) 
(list 714.585 -207.7434) 
(list 640.5625 -197.357) 
(list 640.5625 -196.357) 
(list 640.5625 -196.357) 
(list 640.2625 -186.357) 
(list 639.7375 -186.357) 
(list 639.4375 -196.357) 
(list 639.4375 -196.357) 
(list 639.4375 -197.357) 
(list 565.415 -207.7434) 
(list 565.415 -212.6864) 
(list 639.4375 -200.8) 
(list 639.4375 -201.8) 
(list 639.4375 -201.8) 
(list 639.815 -211.8)))
(apply 'command (append '("pline") coords '("c")))
(setq currobj (ssadd (entlast) currobj))
(command "_layer" "set" "prebias" "")
(setq coords (list 
(list 639.4375 -212.6864) 
(list 639.4375 -200.8) 
(list 565.415 -212.6864) 
(list 565.415 -207.7434) 
(list 639.4375 -197.357) 
(list 639.4375 -186.357) 
(list 640.5625 -186.357) 
(list 640.5625 -197.357) 
(list 714.585 -207.7434) 
(list 714.585 -212.6864) 
(list 640.5625 -200.8) 
(list 640.5625 -212.6864)))
(apply 'command (append '("pline") coords '("c")))
(setq currobj (ssadd (entlast) currobj))
(command "_layer" "set" "nitride" "")
(command "_layer" "set" "fda1" "")
(setq coords (list 
(list 640.5625 -200.657) 
(list 714.585 -212.5434) 
(list 714.585 -212.3664) 
(list 640.5625 -200.58)))
(apply 'command (append '("pline") coords '("c")))
(setq currobj (ssadd (entlast) currobj))
(setq coords (list 
(list 640.5625 -200.437) 
(list 714.585 -212.2234) 
(list 714.585 -212.0464) 
(list 640.5625 -200.36)))
(apply 'command (append '("pline") coords '("c")))
(setq currobj (ssadd (entlast) currobj))
(setq coords (list 
(list 640.5625 -200.217) 
(list 714.585 -211.9034) 
(list 714.585 -211.7264) 
(list 640.5625 -200.14)))
(apply 'command (append '("pline") coords '("c")))
(setq currobj (ssadd (entlast) currobj))
(setq coords (list 
(list 640.5625 -199.997) 
(list 714.585 -211.5834) 
(list 714.585 -211.4064) 
(list 640.5625 -199.92)))
(apply 'command (append '("pline") coords '("c")))
(setq currobj (ssadd (entlast) currobj))
(setq coords (list 
(list 640.5625 -199.777) 
(list 714.585 -211.2634) 
(list 714.585 -211.0864) 
(list 640.5625 -199.7)))
(apply 'command (append '("pline") coords '("c")))
(setq currobj (ssadd (entlast) currobj))
(setq coords (list 
(list 640.5625 -199.557) 
(list 714.585 -210.9434) 
(list 714.585 -210.7664) 
(list 640.5625 -199.48)))
(apply 'command (append '("pline") coords '("c")))
(setq currobj (ssadd (entlast) currobj))
(setq coords (list 
(list 640.5625 -199.337) 
(list 714.585 -210.6234) 
(list 714.585 -210.4464) 
(list 640.5625 -199.26)))
(apply 'command (append '("pline") coords '("c")))
(setq currobj (ssadd (entlast) currobj))
(setq coords (list 
(list 640.5625 -199.117) 
(list 714.585 -210.3034) 
(list 714.585 -210.1264) 
(list 640.5625 -199.04)))
(apply 'command (append '("pline") coords '("c")))
(setq currobj (ssadd (entlast) currobj))
(setq coords (list 
(list 640.5625 -198.897) 
(list 714.585 -209.9834) 
(list 714.585 -209.8064) 
(list 640.5625 -198.82)))
(apply 'command (append '("pline") coords '("c")))
(setq currobj (ssadd (entlast) currobj))
(setq coords (list 
(list 640.5625 -198.677) 
(list 714.585 -209.6634) 
(list 714.585 -209.4864) 
(list 640.5625 -198.6)))
(apply 'command (append '("pline") coords '("c")))
(setq currobj (ssadd (entlast) currobj))
(setq coords (list 
(list 640.5625 -198.457) 
(list 714.585 -209.3434) 
(list 714.585 -209.1664) 
(list 640.5625 -198.38)))
(apply 'command (append '("pline") coords '("c")))
(setq currobj (ssadd (entlast) currobj))
(setq coords (list 
(list 640.5625 -198.237) 
(list 714.585 -209.0234) 
(list 714.585 -208.8464) 
(list 640.5625 -198.16)))
(apply 'command (append '("pline") coords '("c")))
(setq currobj (ssadd (entlast) currobj))
(setq coords (list 
(list 640.5625 -198.017) 
(list 714.585 -208.7034) 
(list 714.585 -208.5264) 
(list 640.5625 -197.94)))
(apply 'command (append '("pline") coords '("c")))
(setq currobj (ssadd (entlast) currobj))
(setq coords (list 
(list 640.5625 -197.797) 
(list 714.585 -208.3834) 
(list 714.585 -208.2064) 
(list 640.5625 -197.72)))
(apply 'command (append '("pline") coords '("c")))
(setq currobj (ssadd (entlast) currobj))
(setq coords (list 
(list 640.5625 -197.577) 
(list 714.585 -208.0634) 
(list 714.585 -207.8864) 
(list 640.5625 -197.5)))
(apply 'command (append '("pline") coords '("c")))
(setq currobj (ssadd (entlast) currobj))
(setq coords (list 
(list 639.4375 -197.5) 
(list 565.415 -207.8864) 
(list 565.415 -208.0634) 
(list 639.4375 -197.577)))
(apply 'command (append '("pline") coords '("c")))
(setq currobj (ssadd (entlast) currobj))
(setq coords (list 
(list 639.4375 -197.72) 
(list 565.415 -208.2064) 
(list 565.415 -208.3834) 
(list 639.4375 -197.797)))
(apply 'command (append '("pline") coords '("c")))
(setq currobj (ssadd (entlast) currobj))
(setq coords (list 
(list 639.4375 -197.94) 
(list 565.415 -208.5264) 
(list 565.415 -208.7034) 
(list 639.4375 -198.017)))
(apply 'command (append '("pline") coords '("c")))
(setq currobj (ssadd (entlast) currobj))
(setq coords (list 
(list 639.4375 -198.16) 
(list 565.415 -208.8464) 
(list 565.415 -209.0234) 
(list 639.4375 -198.237)))
(apply 'command (append '("pline") coords '("c")))
(setq currobj (ssadd (entlast) currobj))
(setq coords (list 
(list 639.4375 -198.38) 
(list 565.415 -209.1664) 
(list 565.415 -209.3434) 
(list 639.4375 -198.457)))
(apply 'command (append '("pline") coords '("c")))
(setq currobj (ssadd (entlast) currobj))
(setq coords (list 
(list 639.4375 -198.6) 
(list 565.415 -209.4864) 
(list 565.415 -209.6634) 
(list 639.4375 -198.677)))
(apply 'command (append '("pline") coords '("c")))
(setq currobj (ssadd (entlast) currobj))
(setq coords (list 
(list 639.4375 -198.82) 
(list 565.415 -209.8064) 
(list 565.415 -209.9834) 
(list 639.4375 -198.897)))
(apply 'command (append '("pline") coords '("c")))
(setq currobj (ssadd (entlast) currobj))
(setq coords (list 
(list 639.4375 -199.04) 
(list 565.415 -210.1264) 
(list 565.415 -210.3034) 
(list 639.4375 -199.117)))
(apply 'command (append '("pline") coords '("c")))
(setq currobj (ssadd (entlast) currobj))
(setq coords (list 
(list 639.4375 -199.26) 
(list 565.415 -210.4464) 
(list 565.415 -210.6234) 
(list 639.4375 -199.337)))
(apply 'command (append '("pline") coords '("c")))
(setq currobj (ssadd (entlast) currobj))
(setq coords (list 
(list 639.4375 -199.48) 
(list 565.415 -210.7664) 
(list 565.415 -210.9434) 
(list 639.4375 -199.557)))
(apply 'command (append '("pline") coords '("c")))
(setq currobj (ssadd (entlast) currobj))
(setq coords (list 
(list 639.4375 -199.7) 
(list 565.415 -211.0864) 
(list 565.415 -211.2634) 
(list 639.4375 -199.777)))
(apply 'command (append '("pline") coords '("c")))
(setq currobj (ssadd (entlast) currobj))
(setq coords (list 
(list 639.4375 -199.92) 
(list 565.415 -211.4064) 
(list 565.415 -211.5834) 
(list 639.4375 -199.997)))
(apply 'command (append '("pline") coords '("c")))
(setq currobj (ssadd (entlast) currobj))
(setq coords (list 
(list 639.4375 -200.14) 
(list 565.415 -211.7264) 
(list 565.415 -211.9034) 
(list 639.4375 -200.217)))
(apply 'command (append '("pline") coords '("c")))
(setq currobj (ssadd (entlast) currobj))
(setq coords (list 
(list 639.4375 -200.36) 
(list 565.415 -212.0464) 
(list 565.415 -212.2234) 
(list 639.4375 -200.437)))
(apply 'command (append '("pline") coords '("c")))
(setq currobj (ssadd (entlast) currobj))
(setq coords (list 
(list 639.4375 -200.58) 
(list 565.415 -212.3664) 
(list 565.415 -212.5434) 
(list 639.4375 -200.657)))
(apply 'command (append '("pline") coords '("c")))
(setq currobj (ssadd (entlast) currobj))
(command "_layer" "set" "nitride" "")
(command "_layer" "set" "text" "")
(command "_circle" "638.985,-211.8" "0.075")
(command "_circle" "638.985,-211.5" "0.075")
(command "_circle" "638.985,-211.2" "0.075")
(command "_circle" "638.985,-210.9" "0.075")
(command "_circle" "638.985,-210.6" "0.075")
(command "_circle" "638.685,-211.8" "0.075")
(command "_circle" "638.685,-211.5" "0.075")
(command "_circle" "638.685,-211.2" "0.075")
(command "_circle" "638.685,-210.9" "0.075")
(command "_circle" "638.685,-210.6" "0.075")
(command "_circle" "638.385,-211.8" "0.075")
(command "_circle" "638.385,-211.5" "0.075")
(command "_circle" "638.385,-211.2" "0.075")
(command "_circle" "638.385,-210.9" "0.075")
(command "_circle" "638.385,-210.6" "0.075")
(command "_circle" "638.085,-211.8" "0.075")
(command "_circle" "638.085,-211.5" "0.075")
(command "_circle" "638.085,-211.2" "0.075")
(command "_circle" "638.085,-210.9" "0.075")
(command "_circle" "638.085,-210.6" "0.075")
(command "_circle" "637.785,-211.8" "0.075")
(command "_circle" "637.785,-211.5" "0.075")
(command "_circle" "637.785,-211.2" "0.075")
(command "_circle" "637.785,-210.9" "0.075")
(command "_circle" "637.785,-210.6" "0.075")
(command "_layer" "set" "nitride" "")
(setq anglednodearray2 currobj)
(setq currobj nil)
(setq currobj (ssadd))
; DRAWING COOLED SINGLE NANOBEAM
(setq coords (list 
(list 640.2625 -186.357) 
(list 640.2625 -181.357) 
(list 639.7375 -181.357) 
(list 639.7375 -186.357)))
(apply 'command (append '("pline") coords '("c")))
(setq currobj (ssadd (entlast) currobj))
(command "_layer" "set" "prebias" "")
(command "_rectangle" "639.7375,-186.357" "640.2625,-181.357")
(setq currobj (ssadd (entlast) currobj))
(command "_layer" "set" "nitride" "")
(setq coords (list 
(list 640.2625 -181.357) 
(list 640.5625 -171.357) 
(list 640.5625 -171.357) 
(list 640.5625 -170.357) 
(list 714.585 -171.107) 
(list 714.585 -166.164) 
(list 640.5625 -166.914) 
(list 640.5625 -165.914) 
(list 640.5625 -165.914) 
(list 640.2625 -155.914) 
(list 639.7375 -155.914) 
(list 639.4375 -165.914) 
(list 639.4375 -165.914) 
(list 639.4375 -166.914) 
(list 565.415 -166.164) 
(list 565.415 -171.107) 
(list 639.4375 -170.357) 
(list 639.4375 -171.357) 
(list 639.4375 -171.357) 
(list 639.7375 -181.357)))
(apply 'command (append '("pline") coords '("c")))
(setq currobj (ssadd (entlast) currobj))
(command "_layer" "set" "prebias" "")
(setq coords (list 
(list 639.4375 -181.357) 
(list 639.4375 -170.357) 
(list 565.415 -171.107) 
(list 565.415 -166.164) 
(list 639.4375 -166.914) 
(list 639.4375 -155.914) 
(list 640.5625 -155.914) 
(list 640.5625 -166.914) 
(list 714.585 -166.164) 
(list 714.585 -171.107) 
(list 640.5625 -170.357) 
(list 640.5625 -181.357)))
(apply 'command (append '("pline") coords '("c")))
(setq currobj (ssadd (entlast) currobj))
(command "_layer" "set" "nitride" "")
(command "_layer" "set" "fda1" "")
(setq coords (list 
(list 640.5625 -170.214) 
(list 714.585 -170.964) 
(list 714.585 -170.787) 
(list 640.5625 -170.137)))
(apply 'command (append '("pline") coords '("c")))
(setq currobj (ssadd (entlast) currobj))
(setq coords (list 
(list 640.5625 -169.994) 
(list 714.585 -170.644) 
(list 714.585 -170.467) 
(list 640.5625 -169.917)))
(apply 'command (append '("pline") coords '("c")))
(setq currobj (ssadd (entlast) currobj))
(setq coords (list 
(list 640.5625 -169.774) 
(list 714.585 -170.324) 
(list 714.585 -170.147) 
(list 640.5625 -169.697)))
(apply 'command (append '("pline") coords '("c")))
(setq currobj (ssadd (entlast) currobj))
(setq coords (list 
(list 640.5625 -169.554) 
(list 714.585 -170.004) 
(list 714.585 -169.827) 
(list 640.5625 -169.477)))
(apply 'command (append '("pline") coords '("c")))
(setq currobj (ssadd (entlast) currobj))
(setq coords (list 
(list 640.5625 -169.334) 
(list 714.585 -169.684) 
(list 714.585 -169.507) 
(list 640.5625 -169.257)))
(apply 'command (append '("pline") coords '("c")))
(setq currobj (ssadd (entlast) currobj))
(setq coords (list 
(list 640.5625 -169.114) 
(list 714.585 -169.364) 
(list 714.585 -169.187) 
(list 640.5625 -169.037)))
(apply 'command (append '("pline") coords '("c")))
(setq currobj (ssadd (entlast) currobj))
(setq coords (list 
(list 640.5625 -168.894) 
(list 714.585 -169.044) 
(list 714.585 -168.867) 
(list 640.5625 -168.817)))
(apply 'command (append '("pline") coords '("c")))
(setq currobj (ssadd (entlast) currobj))
(setq coords (list 
(list 640.5625 -168.674) 
(list 714.585 -168.724) 
(list 714.585 -168.547) 
(list 640.5625 -168.597)))
(apply 'command (append '("pline") coords '("c")))
(setq currobj (ssadd (entlast) currobj))
(setq coords (list 
(list 640.5625 -168.454) 
(list 714.585 -168.404) 
(list 714.585 -168.227) 
(list 640.5625 -168.377)))
(apply 'command (append '("pline") coords '("c")))
(setq currobj (ssadd (entlast) currobj))
(setq coords (list 
(list 640.5625 -168.234) 
(list 714.585 -168.084) 
(list 714.585 -167.907) 
(list 640.5625 -168.157)))
(apply 'command (append '("pline") coords '("c")))
(setq currobj (ssadd (entlast) currobj))
(setq coords (list 
(list 640.5625 -168.014) 
(list 714.585 -167.764) 
(list 714.585 -167.587) 
(list 640.5625 -167.937)))
(apply 'command (append '("pline") coords '("c")))
(setq currobj (ssadd (entlast) currobj))
(setq coords (list 
(list 640.5625 -167.794) 
(list 714.585 -167.444) 
(list 714.585 -167.267) 
(list 640.5625 -167.717)))
(apply 'command (append '("pline") coords '("c")))
(setq currobj (ssadd (entlast) currobj))
(setq coords (list 
(list 640.5625 -167.574) 
(list 714.585 -167.124) 
(list 714.585 -166.947) 
(list 640.5625 -167.497)))
(apply 'command (append '("pline") coords '("c")))
(setq currobj (ssadd (entlast) currobj))
(setq coords (list 
(list 640.5625 -167.354) 
(list 714.585 -166.804) 
(list 714.585 -166.627) 
(list 640.5625 -167.277)))
(apply 'command (append '("pline") coords '("c")))
(setq currobj (ssadd (entlast) currobj))
(setq coords (list 
(list 640.5625 -167.134) 
(list 714.585 -166.484) 
(list 714.585 -166.307) 
(list 640.5625 -167.057)))
(apply 'command (append '("pline") coords '("c")))
(setq currobj (ssadd (entlast) currobj))
(setq coords (list 
(list 639.4375 -167.057) 
(list 565.415 -166.307) 
(list 565.415 -166.484) 
(list 639.4375 -167.134)))
(apply 'command (append '("pline") coords '("c")))
(setq currobj (ssadd (entlast) currobj))
(setq coords (list 
(list 639.4375 -167.277) 
(list 565.415 -166.627) 
(list 565.415 -166.804) 
(list 639.4375 -167.354)))
(apply 'command (append '("pline") coords '("c")))
(setq currobj (ssadd (entlast) currobj))
(setq coords (list 
(list 639.4375 -167.497) 
(list 565.415 -166.947) 
(list 565.415 -167.124) 
(list 639.4375 -167.574)))
(apply 'command (append '("pline") coords '("c")))
(setq currobj (ssadd (entlast) currobj))
(setq coords (list 
(list 639.4375 -167.717) 
(list 565.415 -167.267) 
(list 565.415 -167.444) 
(list 639.4375 -167.794)))
(apply 'command (append '("pline") coords '("c")))
(setq currobj (ssadd (entlast) currobj))
(setq coords (list 
(list 639.4375 -167.937) 
(list 565.415 -167.587) 
(list 565.415 -167.764) 
(list 639.4375 -168.014)))
(apply 'command (append '("pline") coords '("c")))
(setq currobj (ssadd (entlast) currobj))
(setq coords (list 
(list 639.4375 -168.157) 
(list 565.415 -167.907) 
(list 565.415 -168.084) 
(list 639.4375 -168.234)))
(apply 'command (append '("pline") coords '("c")))
(setq currobj (ssadd (entlast) currobj))
(setq coords (list 
(list 639.4375 -168.377) 
(list 565.415 -168.227) 
(list 565.415 -168.404) 
(list 639.4375 -168.454)))
(apply 'command (append '("pline") coords '("c")))
(setq currobj (ssadd (entlast) currobj))
(setq coords (list 
(list 639.4375 -168.597) 
(list 565.415 -168.547) 
(list 565.415 -168.724) 
(list 639.4375 -168.674)))
(apply 'command (append '("pline") coords '("c")))
(setq currobj (ssadd (entlast) currobj))
(setq coords (list 
(list 639.4375 -168.817) 
(list 565.415 -168.867) 
(list 565.415 -169.044) 
(list 639.4375 -168.894)))
(apply 'command (append '("pline") coords '("c")))
(setq currobj (ssadd (entlast) currobj))
(setq coords (list 
(list 639.4375 -169.037) 
(list 565.415 -169.187) 
(list 565.415 -169.364) 
(list 639.4375 -169.114)))
(apply 'command (append '("pline") coords '("c")))
(setq currobj (ssadd (entlast) currobj))
(setq coords (list 
(list 639.4375 -169.257) 
(list 565.415 -169.507) 
(list 565.415 -169.684) 
(list 639.4375 -169.334)))
(apply 'command (append '("pline") coords '("c")))
(setq currobj (ssadd (entlast) currobj))
(setq coords (list 
(list 639.4375 -169.477) 
(list 565.415 -169.827) 
(list 565.415 -170.004) 
(list 639.4375 -169.554)))
(apply 'command (append '("pline") coords '("c")))
(setq currobj (ssadd (entlast) currobj))
(setq coords (list 
(list 639.4375 -169.697) 
(list 565.415 -170.147) 
(list 565.415 -170.324) 
(list 639.4375 -169.774)))
(apply 'command (append '("pline") coords '("c")))
(setq currobj (ssadd (entlast) currobj))
(setq coords (list 
(list 639.4375 -169.917) 
(list 565.415 -170.467) 
(list 565.415 -170.644) 
(list 639.4375 -169.994)))
(apply 'command (append '("pline") coords '("c")))
(setq currobj (ssadd (entlast) currobj))
(setq coords (list 
(list 639.4375 -170.137) 
(list 565.415 -170.787) 
(list 565.415 -170.964) 
(list 639.4375 -170.214)))
(apply 'command (append '("pline") coords '("c")))
(setq currobj (ssadd (entlast) currobj))
(command "_layer" "set" "nitride" "")
(command "_layer" "set" "text" "")
(command "_circle" "639.0625,-181.357" "0.075")
(command "_circle" "639.0625,-181.057" "0.075")
(command "_circle" "639.0625,-180.757" "0.075")
(command "_circle" "639.0625,-180.457" "0.075")
(command "_circle" "639.0625,-180.157" "0.075")
(command "_circle" "638.7625,-181.357" "0.075")
(command "_circle" "638.7625,-181.057" "0.075")
(command "_circle" "638.7625,-180.757" "0.075")
(command "_circle" "638.7625,-180.457" "0.075")
(command "_circle" "638.7625,-180.157" "0.075")
(command "_circle" "638.4625,-181.357" "0.075")
(command "_circle" "638.4625,-181.057" "0.075")
(command "_circle" "638.4625,-180.757" "0.075")
(command "_circle" "638.4625,-180.457" "0.075")
(command "_circle" "638.4625,-180.157" "0.075")
(command "_circle" "638.1625,-181.357" "0.075")
(command "_circle" "638.1625,-181.057" "0.075")
(command "_circle" "638.1625,-180.757" "0.075")
(command "_circle" "638.1625,-180.457" "0.075")
(command "_circle" "638.1625,-180.157" "0.075")
(command "_circle" "637.8625,-181.357" "0.075")
(command "_circle" "637.8625,-181.057" "0.075")
(command "_circle" "637.8625,-180.757" "0.075")
(command "_circle" "637.8625,-180.457" "0.075")
(command "_circle" "637.8625,-180.157" "0.075")
(command "_layer" "set" "nitride" "")
(setq coords (list 
(list 640.2625 -155.914) 
(list 640.2625 -40.2693) 
(list 639.7375 -40.2693) 
(list 639.7375 -155.914)))
(apply 'command (append '("pline") coords '("c")))
(setq currobj (ssadd (entlast) currobj))
(command "_layer" "set" "prebias" "")
(command "_rectangle" "639.7375,-155.914" "640.2625,-40.2693")
(setq currobj (ssadd (entlast) currobj))
(command "_layer" "set" "nitride" "")
(setq coords (list 
(list 640.2625 -40.2693) 
(list 640.5625 -30.2693) 
(list 640.5625 -30.2693) 
(list 640.5625 -29.2693) 
(list 714.585 -30.0193) 
(list 714.585 -25.0763) 
(list 640.5625 -25.8263) 
(list 640.5625 -24.8263) 
(list 640.5625 -24.8263) 
(list 640.2625 -14.8263) 
(list 639.7375 -14.8263) 
(list 639.4375 -24.8263) 
(list 639.4375 -24.8263) 
(list 639.4375 -25.8263) 
(list 565.415 -25.0763) 
(list 565.415 -30.0193) 
(list 639.4375 -29.2693) 
(list 639.4375 -30.2693) 
(list 639.4375 -30.2693) 
(list 639.7375 -40.2693)))
(apply 'command (append '("pline") coords '("c")))
(setq currobj (ssadd (entlast) currobj))
(command "_layer" "set" "prebias" "")
(setq coords (list 
(list 639.4375 -40.2693) 
(list 639.4375 -29.2693) 
(list 565.415 -30.0193) 
(list 565.415 -25.0763) 
(list 639.4375 -25.8263) 
(list 639.4375 -14.8263) 
(list 640.5625 -14.8263) 
(list 640.5625 -25.8263) 
(list 714.585 -25.0763) 
(list 714.585 -30.0193) 
(list 640.5625 -29.2693) 
(list 640.5625 -40.2693)))
(apply 'command (append '("pline") coords '("c")))
(setq currobj (ssadd (entlast) currobj))
(command "_layer" "set" "nitride" "")
(command "_layer" "set" "fda1" "")
(setq coords (list 
(list 640.5625 -29.1263) 
(list 714.585 -29.8763) 
(list 714.585 -29.6993) 
(list 640.5625 -29.0493)))
(apply 'command (append '("pline") coords '("c")))
(setq currobj (ssadd (entlast) currobj))
(setq coords (list 
(list 640.5625 -28.9063) 
(list 714.585 -29.5563) 
(list 714.585 -29.3793) 
(list 640.5625 -28.8293)))
(apply 'command (append '("pline") coords '("c")))
(setq currobj (ssadd (entlast) currobj))
(setq coords (list 
(list 640.5625 -28.6863) 
(list 714.585 -29.2363) 
(list 714.585 -29.0593) 
(list 640.5625 -28.6093)))
(apply 'command (append '("pline") coords '("c")))
(setq currobj (ssadd (entlast) currobj))
(setq coords (list 
(list 640.5625 -28.4663) 
(list 714.585 -28.9163) 
(list 714.585 -28.7393) 
(list 640.5625 -28.3893)))
(apply 'command (append '("pline") coords '("c")))
(setq currobj (ssadd (entlast) currobj))
(setq coords (list 
(list 640.5625 -28.2463) 
(list 714.585 -28.5963) 
(list 714.585 -28.4193) 
(list 640.5625 -28.1693)))
(apply 'command (append '("pline") coords '("c")))
(setq currobj (ssadd (entlast) currobj))
(setq coords (list 
(list 640.5625 -28.0263) 
(list 714.585 -28.2763) 
(list 714.585 -28.0993) 
(list 640.5625 -27.9493)))
(apply 'command (append '("pline") coords '("c")))
(setq currobj (ssadd (entlast) currobj))
(setq coords (list 
(list 640.5625 -27.8063) 
(list 714.585 -27.9563) 
(list 714.585 -27.7793) 
(list 640.5625 -27.7293)))
(apply 'command (append '("pline") coords '("c")))
(setq currobj (ssadd (entlast) currobj))
(setq coords (list 
(list 640.5625 -27.5863) 
(list 714.585 -27.6363) 
(list 714.585 -27.4593) 
(list 640.5625 -27.5093)))
(apply 'command (append '("pline") coords '("c")))
(setq currobj (ssadd (entlast) currobj))
(setq coords (list 
(list 640.5625 -27.3663) 
(list 714.585 -27.3163) 
(list 714.585 -27.1393) 
(list 640.5625 -27.2893)))
(apply 'command (append '("pline") coords '("c")))
(setq currobj (ssadd (entlast) currobj))
(setq coords (list 
(list 640.5625 -27.1463) 
(list 714.585 -26.9963) 
(list 714.585 -26.8193) 
(list 640.5625 -27.0693)))
(apply 'command (append '("pline") coords '("c")))
(setq currobj (ssadd (entlast) currobj))
(setq coords (list 
(list 640.5625 -26.9263) 
(list 714.585 -26.6763) 
(list 714.585 -26.4993) 
(list 640.5625 -26.8493)))
(apply 'command (append '("pline") coords '("c")))
(setq currobj (ssadd (entlast) currobj))
(setq coords (list 
(list 640.5625 -26.7063) 
(list 714.585 -26.3563) 
(list 714.585 -26.1793) 
(list 640.5625 -26.6293)))
(apply 'command (append '("pline") coords '("c")))
(setq currobj (ssadd (entlast) currobj))
(setq coords (list 
(list 640.5625 -26.4863) 
(list 714.585 -26.0363) 
(list 714.585 -25.8593) 
(list 640.5625 -26.4093)))
(apply 'command (append '("pline") coords '("c")))
(setq currobj (ssadd (entlast) currobj))
(setq coords (list 
(list 640.5625 -26.2663) 
(list 714.585 -25.7163) 
(list 714.585 -25.5393) 
(list 640.5625 -26.1893)))
(apply 'command (append '("pline") coords '("c")))
(setq currobj (ssadd (entlast) currobj))
(setq coords (list 
(list 640.5625 -26.0463) 
(list 714.585 -25.3963) 
(list 714.585 -25.2193) 
(list 640.5625 -25.9693)))
(apply 'command (append '("pline") coords '("c")))
(setq currobj (ssadd (entlast) currobj))
(setq coords (list 
(list 639.4375 -25.9693) 
(list 565.415 -25.2193) 
(list 565.415 -25.3963) 
(list 639.4375 -26.0463)))
(apply 'command (append '("pline") coords '("c")))
(setq currobj (ssadd (entlast) currobj))
(setq coords (list 
(list 639.4375 -26.1893) 
(list 565.415 -25.5393) 
(list 565.415 -25.7163) 
(list 639.4375 -26.2663)))
(apply 'command (append '("pline") coords '("c")))
(setq currobj (ssadd (entlast) currobj))
(setq coords (list 
(list 639.4375 -26.4093) 
(list 565.415 -25.8593) 
(list 565.415 -26.0363) 
(list 639.4375 -26.4863)))
(apply 'command (append '("pline") coords '("c")))
(setq currobj (ssadd (entlast) currobj))
(setq coords (list 
(list 639.4375 -26.6293) 
(list 565.415 -26.1793) 
(list 565.415 -26.3563) 
(list 639.4375 -26.7063)))
(apply 'command (append '("pline") coords '("c")))
(setq currobj (ssadd (entlast) currobj))
(setq coords (list 
(list 639.4375 -26.8493) 
(list 565.415 -26.4993) 
(list 565.415 -26.6763) 
(list 639.4375 -26.9263)))
(apply 'command (append '("pline") coords '("c")))
(setq currobj (ssadd (entlast) currobj))
(setq coords (list 
(list 639.4375 -27.0693) 
(list 565.415 -26.8193) 
(list 565.415 -26.9963) 
(list 639.4375 -27.1463)))
(apply 'command (append '("pline") coords '("c")))
(setq currobj (ssadd (entlast) currobj))
(setq coords (list 
(list 639.4375 -27.2893) 
(list 565.415 -27.1393) 
(list 565.415 -27.3163) 
(list 639.4375 -27.3663)))
(apply 'command (append '("pline") coords '("c")))
(setq currobj (ssadd (entlast) currobj))
(setq coords (list 
(list 639.4375 -27.5093) 
(list 565.415 -27.4593) 
(list 565.415 -27.6363) 
(list 639.4375 -27.5863)))
(apply 'command (append '("pline") coords '("c")))
(setq currobj (ssadd (entlast) currobj))
(setq coords (list 
(list 639.4375 -27.7293) 
(list 565.415 -27.7793) 
(list 565.415 -27.9563) 
(list 639.4375 -27.8063)))
(apply 'command (append '("pline") coords '("c")))
(setq currobj (ssadd (entlast) currobj))
(setq coords (list 
(list 639.4375 -27.9493) 
(list 565.415 -28.0993) 
(list 565.415 -28.2763) 
(list 639.4375 -28.0263)))
(apply 'command (append '("pline") coords '("c")))
(setq currobj (ssadd (entlast) currobj))
(setq coords (list 
(list 639.4375 -28.1693) 
(list 565.415 -28.4193) 
(list 565.415 -28.5963) 
(list 639.4375 -28.2463)))
(apply 'command (append '("pline") coords '("c")))
(setq currobj (ssadd (entlast) currobj))
(setq coords (list 
(list 639.4375 -28.3893) 
(list 565.415 -28.7393) 
(list 565.415 -28.9163) 
(list 639.4375 -28.4663)))
(apply 'command (append '("pline") coords '("c")))
(setq currobj (ssadd (entlast) currobj))
(setq coords (list 
(list 639.4375 -28.6093) 
(list 565.415 -29.0593) 
(list 565.415 -29.2363) 
(list 639.4375 -28.6863)))
(apply 'command (append '("pline") coords '("c")))
(setq currobj (ssadd (entlast) currobj))
(setq coords (list 
(list 639.4375 -28.8293) 
(list 565.415 -29.3793) 
(list 565.415 -29.5563) 
(list 639.4375 -28.9063)))
(apply 'command (append '("pline") coords '("c")))
(setq currobj (ssadd (entlast) currobj))
(setq coords (list 
(list 639.4375 -29.0493) 
(list 565.415 -29.6993) 
(list 565.415 -29.8763) 
(list 639.4375 -29.1263)))
(apply 'command (append '("pline") coords '("c")))
(setq currobj (ssadd (entlast) currobj))
(command "_layer" "set" "nitride" "")
(command "_layer" "set" "text" "")
(command "_circle" "639.0625,-40.2693" "0.075")
(command "_circle" "639.0625,-39.9693" "0.075")
(command "_circle" "639.0625,-39.6693" "0.075")
(command "_circle" "639.0625,-39.3693" "0.075")
(command "_circle" "639.0625,-39.0693" "0.075")
(command "_circle" "638.7625,-40.2693" "0.075")
(command "_circle" "638.7625,-39.9693" "0.075")
(command "_circle" "638.7625,-39.6693" "0.075")
(command "_circle" "638.7625,-39.3693" "0.075")
(command "_circle" "638.7625,-39.0693" "0.075")
(command "_circle" "638.4625,-40.2693" "0.075")
(command "_circle" "638.4625,-39.9693" "0.075")
(command "_circle" "638.4625,-39.6693" "0.075")
(command "_circle" "638.4625,-39.3693" "0.075")
(command "_circle" "638.4625,-39.0693" "0.075")
(command "_circle" "638.1625,-40.2693" "0.075")
(command "_circle" "638.1625,-39.9693" "0.075")
(command "_circle" "638.1625,-39.6693" "0.075")
(command "_circle" "638.1625,-39.3693" "0.075")
(command "_circle" "638.1625,-39.0693" "0.075")
(command "_circle" "637.8625,-40.2693" "0.075")
(command "_circle" "637.8625,-39.9693" "0.075")
(command "_circle" "637.8625,-39.6693" "0.075")
(command "_circle" "637.8625,-39.3693" "0.075")
(command "_circle" "637.8625,-39.0693" "0.075")
(command "_layer" "set" "nitride" "")
(setq coords (list 
(list 640.2625 -14.8263) 
(list 640.2625 100.8184) 
(list 639.7375 100.8184) 
(list 639.7375 -14.8263)))
(apply 'command (append '("pline") coords '("c")))
(setq currobj (ssadd (entlast) currobj))
(command "_layer" "set" "prebias" "")
(command "_rectangle" "639.7375,-14.8263" "640.2625,100.8184")
(setq currobj (ssadd (entlast) currobj))
(command "_layer" "set" "nitride" "")
(setq coords (list 
(list 640.2625 100.8184) 
(list 640.5625 110.8184) 
(list 640.5625 110.8184) 
(list 640.5625 111.8184) 
(list 714.585 111.0684) 
(list 714.585 116.0114) 
(list 640.5625 115.2614) 
(list 640.5625 116.2614) 
(list 640.5625 116.2614) 
(list 640.2625 126.2614) 
(list 639.7375 126.2614) 
(list 639.4375 116.2614) 
(list 639.4375 116.2614) 
(list 639.4375 115.2614) 
(list 565.415 116.0114) 
(list 565.415 111.0684) 
(list 639.4375 111.8184) 
(list 639.4375 110.8184) 
(list 639.4375 110.8184) 
(list 639.7375 100.8184)))
(apply 'command (append '("pline") coords '("c")))
(setq currobj (ssadd (entlast) currobj))
(command "_layer" "set" "prebias" "")
(setq coords (list 
(list 639.4375 100.8184) 
(list 639.4375 111.8184) 
(list 565.415 111.0684) 
(list 565.415 116.0114) 
(list 639.4375 115.2614) 
(list 639.4375 126.2614) 
(list 640.5625 126.2614) 
(list 640.5625 115.2614) 
(list 714.585 116.0114) 
(list 714.585 111.0684) 
(list 640.5625 111.8184) 
(list 640.5625 100.8184)))
(apply 'command (append '("pline") coords '("c")))
(setq currobj (ssadd (entlast) currobj))
(command "_layer" "set" "nitride" "")
(command "_layer" "set" "fda1" "")
(setq coords (list 
(list 640.5625 111.9614) 
(list 714.585 111.2114) 
(list 714.585 111.3884) 
(list 640.5625 112.0384)))
(apply 'command (append '("pline") coords '("c")))
(setq currobj (ssadd (entlast) currobj))
(setq coords (list 
(list 640.5625 112.1814) 
(list 714.585 111.5314) 
(list 714.585 111.7084) 
(list 640.5625 112.2584)))
(apply 'command (append '("pline") coords '("c")))
(setq currobj (ssadd (entlast) currobj))
(setq coords (list 
(list 640.5625 112.4014) 
(list 714.585 111.8514) 
(list 714.585 112.0284) 
(list 640.5625 112.4784)))
(apply 'command (append '("pline") coords '("c")))
(setq currobj (ssadd (entlast) currobj))
(setq coords (list 
(list 640.5625 112.6214) 
(list 714.585 112.1714) 
(list 714.585 112.3484) 
(list 640.5625 112.6984)))
(apply 'command (append '("pline") coords '("c")))
(setq currobj (ssadd (entlast) currobj))
(setq coords (list 
(list 640.5625 112.8414) 
(list 714.585 112.4914) 
(list 714.585 112.6684) 
(list 640.5625 112.9184)))
(apply 'command (append '("pline") coords '("c")))
(setq currobj (ssadd (entlast) currobj))
(setq coords (list 
(list 640.5625 113.0614) 
(list 714.585 112.8114) 
(list 714.585 112.9884) 
(list 640.5625 113.1384)))
(apply 'command (append '("pline") coords '("c")))
(setq currobj (ssadd (entlast) currobj))
(setq coords (list 
(list 640.5625 113.2814) 
(list 714.585 113.1314) 
(list 714.585 113.3084) 
(list 640.5625 113.3584)))
(apply 'command (append '("pline") coords '("c")))
(setq currobj (ssadd (entlast) currobj))
(setq coords (list 
(list 640.5625 113.5014) 
(list 714.585 113.4514) 
(list 714.585 113.6284) 
(list 640.5625 113.5784)))
(apply 'command (append '("pline") coords '("c")))
(setq currobj (ssadd (entlast) currobj))
(setq coords (list 
(list 640.5625 113.7214) 
(list 714.585 113.7714) 
(list 714.585 113.9484) 
(list 640.5625 113.7984)))
(apply 'command (append '("pline") coords '("c")))
(setq currobj (ssadd (entlast) currobj))
(setq coords (list 
(list 640.5625 113.9414) 
(list 714.585 114.0914) 
(list 714.585 114.2684) 
(list 640.5625 114.0184)))
(apply 'command (append '("pline") coords '("c")))
(setq currobj (ssadd (entlast) currobj))
(setq coords (list 
(list 640.5625 114.1614) 
(list 714.585 114.4114) 
(list 714.585 114.5884) 
(list 640.5625 114.2384)))
(apply 'command (append '("pline") coords '("c")))
(setq currobj (ssadd (entlast) currobj))
(setq coords (list 
(list 640.5625 114.3814) 
(list 714.585 114.7314) 
(list 714.585 114.9084) 
(list 640.5625 114.4584)))
(apply 'command (append '("pline") coords '("c")))
(setq currobj (ssadd (entlast) currobj))
(setq coords (list 
(list 640.5625 114.6014) 
(list 714.585 115.0514) 
(list 714.585 115.2284) 
(list 640.5625 114.6784)))
(apply 'command (append '("pline") coords '("c")))
(setq currobj (ssadd (entlast) currobj))
(setq coords (list 
(list 640.5625 114.8214) 
(list 714.585 115.3714) 
(list 714.585 115.5484) 
(list 640.5625 114.8984)))
(apply 'command (append '("pline") coords '("c")))
(setq currobj (ssadd (entlast) currobj))
(setq coords (list 
(list 640.5625 115.0414) 
(list 714.585 115.6914) 
(list 714.585 115.8684) 
(list 640.5625 115.1184)))
(apply 'command (append '("pline") coords '("c")))
(setq currobj (ssadd (entlast) currobj))
(setq coords (list 
(list 639.4375 115.1184) 
(list 565.415 115.8684) 
(list 565.415 115.6914) 
(list 639.4375 115.0414)))
(apply 'command (append '("pline") coords '("c")))
(setq currobj (ssadd (entlast) currobj))
(setq coords (list 
(list 639.4375 114.8984) 
(list 565.415 115.5484) 
(list 565.415 115.3714) 
(list 639.4375 114.8214)))
(apply 'command (append '("pline") coords '("c")))
(setq currobj (ssadd (entlast) currobj))
(setq coords (list 
(list 639.4375 114.6784) 
(list 565.415 115.2284) 
(list 565.415 115.0514) 
(list 639.4375 114.6014)))
(apply 'command (append '("pline") coords '("c")))
(setq currobj (ssadd (entlast) currobj))
(setq coords (list 
(list 639.4375 114.4584) 
(list 565.415 114.9084) 
(list 565.415 114.7314) 
(list 639.4375 114.3814)))
(apply 'command (append '("pline") coords '("c")))
(setq currobj (ssadd (entlast) currobj))
(setq coords (list 
(list 639.4375 114.2384) 
(list 565.415 114.5884) 
(list 565.415 114.4114) 
(list 639.4375 114.1614)))
(apply 'command (append '("pline") coords '("c")))
(setq currobj (ssadd (entlast) currobj))
(setq coords (list 
(list 639.4375 114.0184) 
(list 565.415 114.2684) 
(list 565.415 114.0914) 
(list 639.4375 113.9414)))
(apply 'command (append '("pline") coords '("c")))
(setq currobj (ssadd (entlast) currobj))
(setq coords (list 
(list 639.4375 113.7984) 
(list 565.415 113.9484) 
(list 565.415 113.7714) 
(list 639.4375 113.7214)))
(apply 'command (append '("pline") coords '("c")))
(setq currobj (ssadd (entlast) currobj))
(setq coords (list 
(list 639.4375 113.5784) 
(list 565.415 113.6284) 
(list 565.415 113.4514) 
(list 639.4375 113.5014)))
(apply 'command (append '("pline") coords '("c")))
(setq currobj (ssadd (entlast) currobj))
(setq coords (list 
(list 639.4375 113.3584) 
(list 565.415 113.3084) 
(list 565.415 113.1314) 
(list 639.4375 113.2814)))
(apply 'command (append '("pline") coords '("c")))
(setq currobj (ssadd (entlast) currobj))
(setq coords (list 
(list 639.4375 113.1384) 
(list 565.415 112.9884) 
(list 565.415 112.8114) 
(list 639.4375 113.0614)))
(apply 'command (append '("pline") coords '("c")))
(setq currobj (ssadd (entlast) currobj))
(setq coords (list 
(list 639.4375 112.9184) 
(list 565.415 112.6684) 
(list 565.415 112.4914) 
(list 639.4375 112.8414)))
(apply 'command (append '("pline") coords '("c")))
(setq currobj (ssadd (entlast) currobj))
(setq coords (list 
(list 639.4375 112.6984) 
(list 565.415 112.3484) 
(list 565.415 112.1714) 
(list 639.4375 112.6214)))
(apply 'command (append '("pline") coords '("c")))
(setq currobj (ssadd (entlast) currobj))
(setq coords (list 
(list 639.4375 112.4784) 
(list 565.415 112.0284) 
(list 565.415 111.8514) 
(list 639.4375 112.4014)))
(apply 'command (append '("pline") coords '("c")))
(setq currobj (ssadd (entlast) currobj))
(setq coords (list 
(list 639.4375 112.2584) 
(list 565.415 111.7084) 
(list 565.415 111.5314) 
(list 639.4375 112.1814)))
(apply 'command (append '("pline") coords '("c")))
(setq currobj (ssadd (entlast) currobj))
(setq coords (list 
(list 639.4375 112.0384) 
(list 565.415 111.3884) 
(list 565.415 111.2114) 
(list 639.4375 111.9614)))
(apply 'command (append '("pline") coords '("c")))
(setq currobj (ssadd (entlast) currobj))
(command "_layer" "set" "nitride" "")
(command "_layer" "set" "text" "")
(command "_circle" "639.0625,100.8184" "0.075")
(command "_circle" "639.0625,101.1184" "0.075")
(command "_circle" "639.0625,101.4184" "0.075")
(command "_circle" "639.0625,101.7184" "0.075")
(command "_circle" "639.0625,102.0184" "0.075")
(command "_circle" "638.7625,100.8184" "0.075")
(command "_circle" "638.7625,101.1184" "0.075")
(command "_circle" "638.7625,101.4184" "0.075")
(command "_circle" "638.7625,101.7184" "0.075")
(command "_circle" "638.7625,102.0184" "0.075")
(command "_circle" "638.4625,100.8184" "0.075")
(command "_circle" "638.4625,101.1184" "0.075")
(command "_circle" "638.4625,101.4184" "0.075")
(command "_circle" "638.4625,101.7184" "0.075")
(command "_circle" "638.4625,102.0184" "0.075")
(command "_circle" "638.1625,100.8184" "0.075")
(command "_circle" "638.1625,101.1184" "0.075")
(command "_circle" "638.1625,101.4184" "0.075")
(command "_circle" "638.1625,101.7184" "0.075")
(command "_circle" "638.1625,102.0184" "0.075")
(command "_circle" "637.8625,100.8184" "0.075")
(command "_circle" "637.8625,101.1184" "0.075")
(command "_circle" "637.8625,101.4184" "0.075")
(command "_circle" "637.8625,101.7184" "0.075")
(command "_circle" "637.8625,102.0184" "0.075")
(command "_layer" "set" "nitride" "")
(setq coords (list 
(list 640.2625 126.2614) 
(list 640.2625 241.9061) 
(list 639.7375 241.9061) 
(list 639.7375 126.2614)))
(apply 'command (append '("pline") coords '("c")))
(setq currobj (ssadd (entlast) currobj))
(command "_layer" "set" "prebias" "")
(command "_rectangle" "639.7375,126.2614" "640.2625,241.9061")
(setq currobj (ssadd (entlast) currobj))
(command "_layer" "set" "nitride" "")
(setq coords (list 
(list 640.2625 241.9061) 
(list 640.5625 251.9061) 
(list 640.5625 251.9061) 
(list 640.5625 252.9061) 
(list 714.585 252.1561) 
(list 714.585 257.0991) 
(list 640.5625 256.3491) 
(list 640.5625 257.3491) 
(list 640.5625 257.3491) 
(list 640.2625 267.3491) 
(list 639.7375 267.3491) 
(list 639.4375 257.3491) 
(list 639.4375 257.3491) 
(list 639.4375 256.3491) 
(list 565.415 257.0991) 
(list 565.415 252.1561) 
(list 639.4375 252.9061) 
(list 639.4375 251.9061) 
(list 639.4375 251.9061) 
(list 639.7375 241.9061)))
(apply 'command (append '("pline") coords '("c")))
(setq currobj (ssadd (entlast) currobj))
(command "_layer" "set" "prebias" "")
(setq coords (list 
(list 639.4375 241.9061) 
(list 639.4375 252.9061) 
(list 565.415 252.1561) 
(list 565.415 257.0991) 
(list 639.4375 256.3491) 
(list 639.4375 267.3491) 
(list 640.5625 267.3491) 
(list 640.5625 256.3491) 
(list 714.585 257.0991) 
(list 714.585 252.1561) 
(list 640.5625 252.9061) 
(list 640.5625 241.9061)))
(apply 'command (append '("pline") coords '("c")))
(setq currobj (ssadd (entlast) currobj))
(command "_layer" "set" "nitride" "")
(command "_layer" "set" "fda1" "")
(setq coords (list 
(list 640.5625 253.0491) 
(list 714.585 252.2991) 
(list 714.585 252.4761) 
(list 640.5625 253.1261)))
(apply 'command (append '("pline") coords '("c")))
(setq currobj (ssadd (entlast) currobj))
(setq coords (list 
(list 640.5625 253.2691) 
(list 714.585 252.6191) 
(list 714.585 252.7961) 
(list 640.5625 253.3461)))
(apply 'command (append '("pline") coords '("c")))
(setq currobj (ssadd (entlast) currobj))
(setq coords (list 
(list 640.5625 253.4891) 
(list 714.585 252.9391) 
(list 714.585 253.1161) 
(list 640.5625 253.5661)))
(apply 'command (append '("pline") coords '("c")))
(setq currobj (ssadd (entlast) currobj))
(setq coords (list 
(list 640.5625 253.7091) 
(list 714.585 253.2591) 
(list 714.585 253.4361) 
(list 640.5625 253.7861)))
(apply 'command (append '("pline") coords '("c")))
(setq currobj (ssadd (entlast) currobj))
(setq coords (list 
(list 640.5625 253.9291) 
(list 714.585 253.5791) 
(list 714.585 253.7561) 
(list 640.5625 254.0061)))
(apply 'command (append '("pline") coords '("c")))
(setq currobj (ssadd (entlast) currobj))
(setq coords (list 
(list 640.5625 254.1491) 
(list 714.585 253.8991) 
(list 714.585 254.0761) 
(list 640.5625 254.2261)))
(apply 'command (append '("pline") coords '("c")))
(setq currobj (ssadd (entlast) currobj))
(setq coords (list 
(list 640.5625 254.3691) 
(list 714.585 254.2191) 
(list 714.585 254.3961) 
(list 640.5625 254.4461)))
(apply 'command (append '("pline") coords '("c")))
(setq currobj (ssadd (entlast) currobj))
(setq coords (list 
(list 640.5625 254.5891) 
(list 714.585 254.5391) 
(list 714.585 254.7161) 
(list 640.5625 254.6661)))
(apply 'command (append '("pline") coords '("c")))
(setq currobj (ssadd (entlast) currobj))
(setq coords (list 
(list 640.5625 254.8091) 
(list 714.585 254.8591) 
(list 714.585 255.0361) 
(list 640.5625 254.8861)))
(apply 'command (append '("pline") coords '("c")))
(setq currobj (ssadd (entlast) currobj))
(setq coords (list 
(list 640.5625 255.0291) 
(list 714.585 255.1791) 
(list 714.585 255.3561) 
(list 640.5625 255.1061)))
(apply 'command (append '("pline") coords '("c")))
(setq currobj (ssadd (entlast) currobj))
(setq coords (list 
(list 640.5625 255.2491) 
(list 714.585 255.4991) 
(list 714.585 255.6761) 
(list 640.5625 255.3261)))
(apply 'command (append '("pline") coords '("c")))
(setq currobj (ssadd (entlast) currobj))
(setq coords (list 
(list 640.5625 255.4691) 
(list 714.585 255.8191) 
(list 714.585 255.9961) 
(list 640.5625 255.5461)))
(apply 'command (append '("pline") coords '("c")))
(setq currobj (ssadd (entlast) currobj))
(setq coords (list 
(list 640.5625 255.6891) 
(list 714.585 256.1391) 
(list 714.585 256.3161) 
(list 640.5625 255.7661)))
(apply 'command (append '("pline") coords '("c")))
(setq currobj (ssadd (entlast) currobj))
(setq coords (list 
(list 640.5625 255.9091) 
(list 714.585 256.4591) 
(list 714.585 256.6361) 
(list 640.5625 255.9861)))
(apply 'command (append '("pline") coords '("c")))
(setq currobj (ssadd (entlast) currobj))
(setq coords (list 
(list 640.5625 256.1291) 
(list 714.585 256.7791) 
(list 714.585 256.9561) 
(list 640.5625 256.2061)))
(apply 'command (append '("pline") coords '("c")))
(setq currobj (ssadd (entlast) currobj))
(setq coords (list 
(list 639.4375 256.2061) 
(list 565.415 256.9561) 
(list 565.415 256.7791) 
(list 639.4375 256.1291)))
(apply 'command (append '("pline") coords '("c")))
(setq currobj (ssadd (entlast) currobj))
(setq coords (list 
(list 639.4375 255.9861) 
(list 565.415 256.6361) 
(list 565.415 256.4591) 
(list 639.4375 255.9091)))
(apply 'command (append '("pline") coords '("c")))
(setq currobj (ssadd (entlast) currobj))
(setq coords (list 
(list 639.4375 255.7661) 
(list 565.415 256.3161) 
(list 565.415 256.1391) 
(list 639.4375 255.6891)))
(apply 'command (append '("pline") coords '("c")))
(setq currobj (ssadd (entlast) currobj))
(setq coords (list 
(list 639.4375 255.5461) 
(list 565.415 255.9961) 
(list 565.415 255.8191) 
(list 639.4375 255.4691)))
(apply 'command (append '("pline") coords '("c")))
(setq currobj (ssadd (entlast) currobj))
(setq coords (list 
(list 639.4375 255.3261) 
(list 565.415 255.6761) 
(list 565.415 255.4991) 
(list 639.4375 255.2491)))
(apply 'command (append '("pline") coords '("c")))
(setq currobj (ssadd (entlast) currobj))
(setq coords (list 
(list 639.4375 255.1061) 
(list 565.415 255.3561) 
(list 565.415 255.1791) 
(list 639.4375 255.0291)))
(apply 'command (append '("pline") coords '("c")))
(setq currobj (ssadd (entlast) currobj))
(setq coords (list 
(list 639.4375 254.8861) 
(list 565.415 255.0361) 
(list 565.415 254.8591) 
(list 639.4375 254.8091)))
(apply 'command (append '("pline") coords '("c")))
(setq currobj (ssadd (entlast) currobj))
(setq coords (list 
(list 639.4375 254.6661) 
(list 565.415 254.7161) 
(list 565.415 254.5391) 
(list 639.4375 254.5891)))
(apply 'command (append '("pline") coords '("c")))
(setq currobj (ssadd (entlast) currobj))
(setq coords (list 
(list 639.4375 254.4461) 
(list 565.415 254.3961) 
(list 565.415 254.2191) 
(list 639.4375 254.3691)))
(apply 'command (append '("pline") coords '("c")))
(setq currobj (ssadd (entlast) currobj))
(setq coords (list 
(list 639.4375 254.2261) 
(list 565.415 254.0761) 
(list 565.415 253.8991) 
(list 639.4375 254.1491)))
(apply 'command (append '("pline") coords '("c")))
(setq currobj (ssadd (entlast) currobj))
(setq coords (list 
(list 639.4375 254.0061) 
(list 565.415 253.7561) 
(list 565.415 253.5791) 
(list 639.4375 253.9291)))
(apply 'command (append '("pline") coords '("c")))
(setq currobj (ssadd (entlast) currobj))
(setq coords (list 
(list 639.4375 253.7861) 
(list 565.415 253.4361) 
(list 565.415 253.2591) 
(list 639.4375 253.7091)))
(apply 'command (append '("pline") coords '("c")))
(setq currobj (ssadd (entlast) currobj))
(setq coords (list 
(list 639.4375 253.5661) 
(list 565.415 253.1161) 
(list 565.415 252.9391) 
(list 639.4375 253.4891)))
(apply 'command (append '("pline") coords '("c")))
(setq currobj (ssadd (entlast) currobj))
(setq coords (list 
(list 639.4375 253.3461) 
(list 565.415 252.7961) 
(list 565.415 252.6191) 
(list 639.4375 253.2691)))
(apply 'command (append '("pline") coords '("c")))
(setq currobj (ssadd (entlast) currobj))
(setq coords (list 
(list 639.4375 253.1261) 
(list 565.415 252.4761) 
(list 565.415 252.2991) 
(list 639.4375 253.0491)))
(apply 'command (append '("pline") coords '("c")))
(setq currobj (ssadd (entlast) currobj))
(command "_layer" "set" "nitride" "")
(command "_layer" "set" "text" "")
(command "_circle" "639.0625,241.9061" "0.075")
(command "_circle" "639.0625,242.2061" "0.075")
(command "_circle" "639.0625,242.5061" "0.075")
(command "_circle" "639.0625,242.8061" "0.075")
(command "_circle" "639.0625,243.1061" "0.075")
(command "_circle" "638.7625,241.9061" "0.075")
(command "_circle" "638.7625,242.2061" "0.075")
(command "_circle" "638.7625,242.5061" "0.075")
(command "_circle" "638.7625,242.8061" "0.075")
(command "_circle" "638.7625,243.1061" "0.075")
(command "_circle" "638.4625,241.9061" "0.075")
(command "_circle" "638.4625,242.2061" "0.075")
(command "_circle" "638.4625,242.5061" "0.075")
(command "_circle" "638.4625,242.8061" "0.075")
(command "_circle" "638.4625,243.1061" "0.075")
(command "_circle" "638.1625,241.9061" "0.075")
(command "_circle" "638.1625,242.2061" "0.075")
(command "_circle" "638.1625,242.5061" "0.075")
(command "_circle" "638.1625,242.8061" "0.075")
(command "_circle" "638.1625,243.1061" "0.075")
(command "_circle" "637.8625,241.9061" "0.075")
(command "_circle" "637.8625,242.2061" "0.075")
(command "_circle" "637.8625,242.5061" "0.075")
(command "_circle" "637.8625,242.8061" "0.075")
(command "_circle" "637.8625,243.1061" "0.075")
(command "_layer" "set" "nitride" "")
(setq coords (list 
(list 640.2625 267.3491) 
(list 640.2625 382.9939) 
(list 639.7375 382.9939) 
(list 639.7375 267.3491)))
(apply 'command (append '("pline") coords '("c")))
(setq currobj (ssadd (entlast) currobj))
(command "_layer" "set" "prebias" "")
(command "_rectangle" "639.7375,267.3491" "640.2625,382.9939")
(setq currobj (ssadd (entlast) currobj))
(command "_layer" "set" "nitride" "")
(setq coords (list 
(list 640.2625 382.9939) 
(list 640.5625 392.9939) 
(list 640.5625 392.9939) 
(list 640.5625 393.9939) 
(list 714.585 393.2439) 
(list 714.585 398.1869) 
(list 640.5625 397.4369) 
(list 640.5625 398.4369) 
(list 640.5625 398.4369) 
(list 640.2625 408.4369) 
(list 639.7375 408.4369) 
(list 639.4375 398.4369) 
(list 639.4375 398.4369) 
(list 639.4375 397.4369) 
(list 565.415 398.1869) 
(list 565.415 393.2439) 
(list 639.4375 393.9939) 
(list 639.4375 392.9939) 
(list 639.4375 392.9939) 
(list 639.7375 382.9939)))
(apply 'command (append '("pline") coords '("c")))
(setq currobj (ssadd (entlast) currobj))
(command "_layer" "set" "prebias" "")
(setq coords (list 
(list 639.4375 382.9939) 
(list 639.4375 393.9939) 
(list 565.415 393.2439) 
(list 565.415 398.1869) 
(list 639.4375 397.4369) 
(list 639.4375 408.4369) 
(list 640.5625 408.4369) 
(list 640.5625 397.4369) 
(list 714.585 398.1869) 
(list 714.585 393.2439) 
(list 640.5625 393.9939) 
(list 640.5625 382.9939)))
(apply 'command (append '("pline") coords '("c")))
(setq currobj (ssadd (entlast) currobj))
(command "_layer" "set" "nitride" "")
(command "_layer" "set" "fda1" "")
(setq coords (list 
(list 640.5625 394.1369) 
(list 714.585 393.3869) 
(list 714.585 393.5639) 
(list 640.5625 394.2139)))
(apply 'command (append '("pline") coords '("c")))
(setq currobj (ssadd (entlast) currobj))
(setq coords (list 
(list 640.5625 394.3569) 
(list 714.585 393.7069) 
(list 714.585 393.8839) 
(list 640.5625 394.4339)))
(apply 'command (append '("pline") coords '("c")))
(setq currobj (ssadd (entlast) currobj))
(setq coords (list 
(list 640.5625 394.5769) 
(list 714.585 394.0269) 
(list 714.585 394.2039) 
(list 640.5625 394.6539)))
(apply 'command (append '("pline") coords '("c")))
(setq currobj (ssadd (entlast) currobj))
(setq coords (list 
(list 640.5625 394.7969) 
(list 714.585 394.3469) 
(list 714.585 394.5239) 
(list 640.5625 394.8739)))
(apply 'command (append '("pline") coords '("c")))
(setq currobj (ssadd (entlast) currobj))
(setq coords (list 
(list 640.5625 395.0169) 
(list 714.585 394.6669) 
(list 714.585 394.8439) 
(list 640.5625 395.0939)))
(apply 'command (append '("pline") coords '("c")))
(setq currobj (ssadd (entlast) currobj))
(setq coords (list 
(list 640.5625 395.2369) 
(list 714.585 394.9869) 
(list 714.585 395.1639) 
(list 640.5625 395.3139)))
(apply 'command (append '("pline") coords '("c")))
(setq currobj (ssadd (entlast) currobj))
(setq coords (list 
(list 640.5625 395.4569) 
(list 714.585 395.3069) 
(list 714.585 395.4839) 
(list 640.5625 395.5339)))
(apply 'command (append '("pline") coords '("c")))
(setq currobj (ssadd (entlast) currobj))
(setq coords (list 
(list 640.5625 395.6769) 
(list 714.585 395.6269) 
(list 714.585 395.8039) 
(list 640.5625 395.7539)))
(apply 'command (append '("pline") coords '("c")))
(setq currobj (ssadd (entlast) currobj))
(setq coords (list 
(list 640.5625 395.8969) 
(list 714.585 395.9469) 
(list 714.585 396.1239) 
(list 640.5625 395.9739)))
(apply 'command (append '("pline") coords '("c")))
(setq currobj (ssadd (entlast) currobj))
(setq coords (list 
(list 640.5625 396.1169) 
(list 714.585 396.2669) 
(list 714.585 396.4439) 
(list 640.5625 396.1939)))
(apply 'command (append '("pline") coords '("c")))
(setq currobj (ssadd (entlast) currobj))
(setq coords (list 
(list 640.5625 396.3369) 
(list 714.585 396.5869) 
(list 714.585 396.7639) 
(list 640.5625 396.4139)))
(apply 'command (append '("pline") coords '("c")))
(setq currobj (ssadd (entlast) currobj))
(setq coords (list 
(list 640.5625 396.5569) 
(list 714.585 396.9069) 
(list 714.585 397.0839) 
(list 640.5625 396.6339)))
(apply 'command (append '("pline") coords '("c")))
(setq currobj (ssadd (entlast) currobj))
(setq coords (list 
(list 640.5625 396.7769) 
(list 714.585 397.2269) 
(list 714.585 397.4039) 
(list 640.5625 396.8539)))
(apply 'command (append '("pline") coords '("c")))
(setq currobj (ssadd (entlast) currobj))
(setq coords (list 
(list 640.5625 396.9969) 
(list 714.585 397.5469) 
(list 714.585 397.7239) 
(list 640.5625 397.0739)))
(apply 'command (append '("pline") coords '("c")))
(setq currobj (ssadd (entlast) currobj))
(setq coords (list 
(list 640.5625 397.2169) 
(list 714.585 397.8669) 
(list 714.585 398.0439) 
(list 640.5625 397.2939)))
(apply 'command (append '("pline") coords '("c")))
(setq currobj (ssadd (entlast) currobj))
(setq coords (list 
(list 639.4375 397.2939) 
(list 565.415 398.0439) 
(list 565.415 397.8669) 
(list 639.4375 397.2169)))
(apply 'command (append '("pline") coords '("c")))
(setq currobj (ssadd (entlast) currobj))
(setq coords (list 
(list 639.4375 397.0739) 
(list 565.415 397.7239) 
(list 565.415 397.5469) 
(list 639.4375 396.9969)))
(apply 'command (append '("pline") coords '("c")))
(setq currobj (ssadd (entlast) currobj))
(setq coords (list 
(list 639.4375 396.8539) 
(list 565.415 397.4039) 
(list 565.415 397.2269) 
(list 639.4375 396.7769)))
(apply 'command (append '("pline") coords '("c")))
(setq currobj (ssadd (entlast) currobj))
(setq coords (list 
(list 639.4375 396.6339) 
(list 565.415 397.0839) 
(list 565.415 396.9069) 
(list 639.4375 396.5569)))
(apply 'command (append '("pline") coords '("c")))
(setq currobj (ssadd (entlast) currobj))
(setq coords (list 
(list 639.4375 396.4139) 
(list 565.415 396.7639) 
(list 565.415 396.5869) 
(list 639.4375 396.3369)))
(apply 'command (append '("pline") coords '("c")))
(setq currobj (ssadd (entlast) currobj))
(setq coords (list 
(list 639.4375 396.1939) 
(list 565.415 396.4439) 
(list 565.415 396.2669) 
(list 639.4375 396.1169)))
(apply 'command (append '("pline") coords '("c")))
(setq currobj (ssadd (entlast) currobj))
(setq coords (list 
(list 639.4375 395.9739) 
(list 565.415 396.1239) 
(list 565.415 395.9469) 
(list 639.4375 395.8969)))
(apply 'command (append '("pline") coords '("c")))
(setq currobj (ssadd (entlast) currobj))
(setq coords (list 
(list 639.4375 395.7539) 
(list 565.415 395.8039) 
(list 565.415 395.6269) 
(list 639.4375 395.6769)))
(apply 'command (append '("pline") coords '("c")))
(setq currobj (ssadd (entlast) currobj))
(setq coords (list 
(list 639.4375 395.5339) 
(list 565.415 395.4839) 
(list 565.415 395.3069) 
(list 639.4375 395.4569)))
(apply 'command (append '("pline") coords '("c")))
(setq currobj (ssadd (entlast) currobj))
(setq coords (list 
(list 639.4375 395.3139) 
(list 565.415 395.1639) 
(list 565.415 394.9869) 
(list 639.4375 395.2369)))
(apply 'command (append '("pline") coords '("c")))
(setq currobj (ssadd (entlast) currobj))
(setq coords (list 
(list 639.4375 395.0939) 
(list 565.415 394.8439) 
(list 565.415 394.6669) 
(list 639.4375 395.0169)))
(apply 'command (append '("pline") coords '("c")))
(setq currobj (ssadd (entlast) currobj))
(setq coords (list 
(list 639.4375 394.8739) 
(list 565.415 394.5239) 
(list 565.415 394.3469) 
(list 639.4375 394.7969)))
(apply 'command (append '("pline") coords '("c")))
(setq currobj (ssadd (entlast) currobj))
(setq coords (list 
(list 639.4375 394.6539) 
(list 565.415 394.2039) 
(list 565.415 394.0269) 
(list 639.4375 394.5769)))
(apply 'command (append '("pline") coords '("c")))
(setq currobj (ssadd (entlast) currobj))
(setq coords (list 
(list 639.4375 394.4339) 
(list 565.415 393.8839) 
(list 565.415 393.7069) 
(list 639.4375 394.3569)))
(apply 'command (append '("pline") coords '("c")))
(setq currobj (ssadd (entlast) currobj))
(setq coords (list 
(list 639.4375 394.2139) 
(list 565.415 393.5639) 
(list 565.415 393.3869) 
(list 639.4375 394.1369)))
(apply 'command (append '("pline") coords '("c")))
(setq currobj (ssadd (entlast) currobj))
(command "_layer" "set" "nitride" "")
(command "_layer" "set" "text" "")
(command "_circle" "639.0625,382.9939" "0.075")
(command "_circle" "639.0625,383.2939" "0.075")
(command "_circle" "639.0625,383.5939" "0.075")
(command "_circle" "639.0625,383.8939" "0.075")
(command "_circle" "639.0625,384.1939" "0.075")
(command "_circle" "638.7625,382.9939" "0.075")
(command "_circle" "638.7625,383.2939" "0.075")
(command "_circle" "638.7625,383.5939" "0.075")
(command "_circle" "638.7625,383.8939" "0.075")
(command "_circle" "638.7625,384.1939" "0.075")
(command "_circle" "638.4625,382.9939" "0.075")
(command "_circle" "638.4625,383.2939" "0.075")
(command "_circle" "638.4625,383.5939" "0.075")
(command "_circle" "638.4625,383.8939" "0.075")
(command "_circle" "638.4625,384.1939" "0.075")
(command "_circle" "638.1625,382.9939" "0.075")
(command "_circle" "638.1625,383.2939" "0.075")
(command "_circle" "638.1625,383.5939" "0.075")
(command "_circle" "638.1625,383.8939" "0.075")
(command "_circle" "638.1625,384.1939" "0.075")
(command "_circle" "637.8625,382.9939" "0.075")
(command "_circle" "637.8625,383.2939" "0.075")
(command "_circle" "637.8625,383.5939" "0.075")
(command "_circle" "637.8625,383.8939" "0.075")
(command "_circle" "637.8625,384.1939" "0.075")
(command "_layer" "set" "nitride" "")
(setq coords (list 
(list 640.2625 408.4369) 
(list 640.2625 524.0816) 
(list 639.7375 524.0816) 
(list 639.7375 408.4369)))
(apply 'command (append '("pline") coords '("c")))
(setq currobj (ssadd (entlast) currobj))
(command "_layer" "set" "prebias" "")
(command "_rectangle" "639.7375,408.4369" "640.2625,524.0816")
(setq currobj (ssadd (entlast) currobj))
(command "_layer" "set" "nitride" "")
(setq coords (list 
(list 640.2625 524.0816) 
(list 640.5625 534.0816) 
(list 640.5625 534.0816) 
(list 640.5625 535.0816) 
(list 714.585 534.3316) 
(list 714.585 539.2746) 
(list 640.5625 538.5246) 
(list 640.5625 539.5246) 
(list 640.5625 539.5246) 
(list 640.2625 549.5246) 
(list 639.7375 549.5246) 
(list 639.4375 539.5246) 
(list 639.4375 539.5246) 
(list 639.4375 538.5246) 
(list 565.415 539.2746) 
(list 565.415 534.3316) 
(list 639.4375 535.0816) 
(list 639.4375 534.0816) 
(list 639.4375 534.0816) 
(list 639.7375 524.0816)))
(apply 'command (append '("pline") coords '("c")))
(setq currobj (ssadd (entlast) currobj))
(command "_layer" "set" "prebias" "")
(setq coords (list 
(list 639.4375 524.0816) 
(list 639.4375 535.0816) 
(list 565.415 534.3316) 
(list 565.415 539.2746) 
(list 639.4375 538.5246) 
(list 639.4375 549.5246) 
(list 640.5625 549.5246) 
(list 640.5625 538.5246) 
(list 714.585 539.2746) 
(list 714.585 534.3316) 
(list 640.5625 535.0816) 
(list 640.5625 524.0816)))
(apply 'command (append '("pline") coords '("c")))
(setq currobj (ssadd (entlast) currobj))
(command "_layer" "set" "nitride" "")
(command "_layer" "set" "fda1" "")
(setq coords (list 
(list 640.5625 535.2246) 
(list 714.585 534.4746) 
(list 714.585 534.6516) 
(list 640.5625 535.3016)))
(apply 'command (append '("pline") coords '("c")))
(setq currobj (ssadd (entlast) currobj))
(setq coords (list 
(list 640.5625 535.4446) 
(list 714.585 534.7946) 
(list 714.585 534.9716) 
(list 640.5625 535.5216)))
(apply 'command (append '("pline") coords '("c")))
(setq currobj (ssadd (entlast) currobj))
(setq coords (list 
(list 640.5625 535.6646) 
(list 714.585 535.1146) 
(list 714.585 535.2916) 
(list 640.5625 535.7416)))
(apply 'command (append '("pline") coords '("c")))
(setq currobj (ssadd (entlast) currobj))
(setq coords (list 
(list 640.5625 535.8846) 
(list 714.585 535.4346) 
(list 714.585 535.6116) 
(list 640.5625 535.9616)))
(apply 'command (append '("pline") coords '("c")))
(setq currobj (ssadd (entlast) currobj))
(setq coords (list 
(list 640.5625 536.1046) 
(list 714.585 535.7546) 
(list 714.585 535.9316) 
(list 640.5625 536.1816)))
(apply 'command (append '("pline") coords '("c")))
(setq currobj (ssadd (entlast) currobj))
(setq coords (list 
(list 640.5625 536.3246) 
(list 714.585 536.0746) 
(list 714.585 536.2516) 
(list 640.5625 536.4016)))
(apply 'command (append '("pline") coords '("c")))
(setq currobj (ssadd (entlast) currobj))
(setq coords (list 
(list 640.5625 536.5446) 
(list 714.585 536.3946) 
(list 714.585 536.5716) 
(list 640.5625 536.6216)))
(apply 'command (append '("pline") coords '("c")))
(setq currobj (ssadd (entlast) currobj))
(setq coords (list 
(list 640.5625 536.7646) 
(list 714.585 536.7146) 
(list 714.585 536.8916) 
(list 640.5625 536.8416)))
(apply 'command (append '("pline") coords '("c")))
(setq currobj (ssadd (entlast) currobj))
(setq coords (list 
(list 640.5625 536.9846) 
(list 714.585 537.0346) 
(list 714.585 537.2116) 
(list 640.5625 537.0616)))
(apply 'command (append '("pline") coords '("c")))
(setq currobj (ssadd (entlast) currobj))
(setq coords (list 
(list 640.5625 537.2046) 
(list 714.585 537.3546) 
(list 714.585 537.5316) 
(list 640.5625 537.2816)))
(apply 'command (append '("pline") coords '("c")))
(setq currobj (ssadd (entlast) currobj))
(setq coords (list 
(list 640.5625 537.4246) 
(list 714.585 537.6746) 
(list 714.585 537.8516) 
(list 640.5625 537.5016)))
(apply 'command (append '("pline") coords '("c")))
(setq currobj (ssadd (entlast) currobj))
(setq coords (list 
(list 640.5625 537.6446) 
(list 714.585 537.9946) 
(list 714.585 538.1716) 
(list 640.5625 537.7216)))
(apply 'command (append '("pline") coords '("c")))
(setq currobj (ssadd (entlast) currobj))
(setq coords (list 
(list 640.5625 537.8646) 
(list 714.585 538.3146) 
(list 714.585 538.4916) 
(list 640.5625 537.9416)))
(apply 'command (append '("pline") coords '("c")))
(setq currobj (ssadd (entlast) currobj))
(setq coords (list 
(list 640.5625 538.0846) 
(list 714.585 538.6346) 
(list 714.585 538.8116) 
(list 640.5625 538.1616)))
(apply 'command (append '("pline") coords '("c")))
(setq currobj (ssadd (entlast) currobj))
(setq coords (list 
(list 640.5625 538.3046) 
(list 714.585 538.9546) 
(list 714.585 539.1316) 
(list 640.5625 538.3816)))
(apply 'command (append '("pline") coords '("c")))
(setq currobj (ssadd (entlast) currobj))
(setq coords (list 
(list 639.4375 538.3816) 
(list 565.415 539.1316) 
(list 565.415 538.9546) 
(list 639.4375 538.3046)))
(apply 'command (append '("pline") coords '("c")))
(setq currobj (ssadd (entlast) currobj))
(setq coords (list 
(list 639.4375 538.1616) 
(list 565.415 538.8116) 
(list 565.415 538.6346) 
(list 639.4375 538.0846)))
(apply 'command (append '("pline") coords '("c")))
(setq currobj (ssadd (entlast) currobj))
(setq coords (list 
(list 639.4375 537.9416) 
(list 565.415 538.4916) 
(list 565.415 538.3146) 
(list 639.4375 537.8646)))
(apply 'command (append '("pline") coords '("c")))
(setq currobj (ssadd (entlast) currobj))
(setq coords (list 
(list 639.4375 537.7216) 
(list 565.415 538.1716) 
(list 565.415 537.9946) 
(list 639.4375 537.6446)))
(apply 'command (append '("pline") coords '("c")))
(setq currobj (ssadd (entlast) currobj))
(setq coords (list 
(list 639.4375 537.5016) 
(list 565.415 537.8516) 
(list 565.415 537.6746) 
(list 639.4375 537.4246)))
(apply 'command (append '("pline") coords '("c")))
(setq currobj (ssadd (entlast) currobj))
(setq coords (list 
(list 639.4375 537.2816) 
(list 565.415 537.5316) 
(list 565.415 537.3546) 
(list 639.4375 537.2046)))
(apply 'command (append '("pline") coords '("c")))
(setq currobj (ssadd (entlast) currobj))
(setq coords (list 
(list 639.4375 537.0616) 
(list 565.415 537.2116) 
(list 565.415 537.0346) 
(list 639.4375 536.9846)))
(apply 'command (append '("pline") coords '("c")))
(setq currobj (ssadd (entlast) currobj))
(setq coords (list 
(list 639.4375 536.8416) 
(list 565.415 536.8916) 
(list 565.415 536.7146) 
(list 639.4375 536.7646)))
(apply 'command (append '("pline") coords '("c")))
(setq currobj (ssadd (entlast) currobj))
(setq coords (list 
(list 639.4375 536.6216) 
(list 565.415 536.5716) 
(list 565.415 536.3946) 
(list 639.4375 536.5446)))
(apply 'command (append '("pline") coords '("c")))
(setq currobj (ssadd (entlast) currobj))
(setq coords (list 
(list 639.4375 536.4016) 
(list 565.415 536.2516) 
(list 565.415 536.0746) 
(list 639.4375 536.3246)))
(apply 'command (append '("pline") coords '("c")))
(setq currobj (ssadd (entlast) currobj))
(setq coords (list 
(list 639.4375 536.1816) 
(list 565.415 535.9316) 
(list 565.415 535.7546) 
(list 639.4375 536.1046)))
(apply 'command (append '("pline") coords '("c")))
(setq currobj (ssadd (entlast) currobj))
(setq coords (list 
(list 639.4375 535.9616) 
(list 565.415 535.6116) 
(list 565.415 535.4346) 
(list 639.4375 535.8846)))
(apply 'command (append '("pline") coords '("c")))
(setq currobj (ssadd (entlast) currobj))
(setq coords (list 
(list 639.4375 535.7416) 
(list 565.415 535.2916) 
(list 565.415 535.1146) 
(list 639.4375 535.6646)))
(apply 'command (append '("pline") coords '("c")))
(setq currobj (ssadd (entlast) currobj))
(setq coords (list 
(list 639.4375 535.5216) 
(list 565.415 534.9716) 
(list 565.415 534.7946) 
(list 639.4375 535.4446)))
(apply 'command (append '("pline") coords '("c")))
(setq currobj (ssadd (entlast) currobj))
(setq coords (list 
(list 639.4375 535.3016) 
(list 565.415 534.6516) 
(list 565.415 534.4746) 
(list 639.4375 535.2246)))
(apply 'command (append '("pline") coords '("c")))
(setq currobj (ssadd (entlast) currobj))
(command "_layer" "set" "nitride" "")
(command "_layer" "set" "text" "")
(command "_circle" "639.0625,524.0816" "0.075")
(command "_circle" "639.0625,524.3816" "0.075")
(command "_circle" "639.0625,524.6816" "0.075")
(command "_circle" "639.0625,524.9816" "0.075")
(command "_circle" "639.0625,525.2816" "0.075")
(command "_circle" "638.7625,524.0816" "0.075")
(command "_circle" "638.7625,524.3816" "0.075")
(command "_circle" "638.7625,524.6816" "0.075")
(command "_circle" "638.7625,524.9816" "0.075")
(command "_circle" "638.7625,525.2816" "0.075")
(command "_circle" "638.4625,524.0816" "0.075")
(command "_circle" "638.4625,524.3816" "0.075")
(command "_circle" "638.4625,524.6816" "0.075")
(command "_circle" "638.4625,524.9816" "0.075")
(command "_circle" "638.4625,525.2816" "0.075")
(command "_circle" "638.1625,524.0816" "0.075")
(command "_circle" "638.1625,524.3816" "0.075")
(command "_circle" "638.1625,524.6816" "0.075")
(command "_circle" "638.1625,524.9816" "0.075")
(command "_circle" "638.1625,525.2816" "0.075")
(command "_circle" "637.8625,524.0816" "0.075")
(command "_circle" "637.8625,524.3816" "0.075")
(command "_circle" "637.8625,524.6816" "0.075")
(command "_circle" "637.8625,524.9816" "0.075")
(command "_circle" "637.8625,525.2816" "0.075")
(command "_layer" "set" "nitride" "")
(setq coords (list 
(list 640.2625 549.5246) 
(list 640.2625 665.1693) 
(list 639.7375 665.1693) 
(list 639.7375 549.5246)))
(apply 'command (append '("pline") coords '("c")))
(setq currobj (ssadd (entlast) currobj))
(command "_layer" "set" "prebias" "")
(command "_rectangle" "639.7375,549.5246" "640.2625,665.1693")
(setq currobj (ssadd (entlast) currobj))
(command "_layer" "set" "nitride" "")
(setq coords (list 
(list 640.2625 665.1693) 
(list 640.5625 675.1693) 
(list 640.5625 675.1693) 
(list 640.5625 676.1693) 
(list 714.585 675.4193) 
(list 714.585 680.3623) 
(list 640.5625 679.6123) 
(list 640.5625 680.6123) 
(list 640.5625 680.6123) 
(list 640.2625 690.6123) 
(list 639.7375 690.6123) 
(list 639.4375 680.6123) 
(list 639.4375 680.6123) 
(list 639.4375 679.6123) 
(list 565.415 680.3623) 
(list 565.415 675.4193) 
(list 639.4375 676.1693) 
(list 639.4375 675.1693) 
(list 639.4375 675.1693) 
(list 639.7375 665.1693)))
(apply 'command (append '("pline") coords '("c")))
(setq currobj (ssadd (entlast) currobj))
(command "_layer" "set" "prebias" "")
(setq coords (list 
(list 639.4375 665.1693) 
(list 639.4375 676.1693) 
(list 565.415 675.4193) 
(list 565.415 680.3623) 
(list 639.4375 679.6123) 
(list 639.4375 690.6123) 
(list 640.5625 690.6123) 
(list 640.5625 679.6123) 
(list 714.585 680.3623) 
(list 714.585 675.4193) 
(list 640.5625 676.1693) 
(list 640.5625 665.1693)))
(apply 'command (append '("pline") coords '("c")))
(setq currobj (ssadd (entlast) currobj))
(command "_layer" "set" "nitride" "")
(command "_layer" "set" "fda1" "")
(setq coords (list 
(list 640.5625 676.3123) 
(list 714.585 675.5623) 
(list 714.585 675.7393) 
(list 640.5625 676.3893)))
(apply 'command (append '("pline") coords '("c")))
(setq currobj (ssadd (entlast) currobj))
(setq coords (list 
(list 640.5625 676.5323) 
(list 714.585 675.8823) 
(list 714.585 676.0593) 
(list 640.5625 676.6093)))
(apply 'command (append '("pline") coords '("c")))
(setq currobj (ssadd (entlast) currobj))
(setq coords (list 
(list 640.5625 676.7523) 
(list 714.585 676.2023) 
(list 714.585 676.3793) 
(list 640.5625 676.8293)))
(apply 'command (append '("pline") coords '("c")))
(setq currobj (ssadd (entlast) currobj))
(setq coords (list 
(list 640.5625 676.9723) 
(list 714.585 676.5223) 
(list 714.585 676.6993) 
(list 640.5625 677.0493)))
(apply 'command (append '("pline") coords '("c")))
(setq currobj (ssadd (entlast) currobj))
(setq coords (list 
(list 640.5625 677.1923) 
(list 714.585 676.8423) 
(list 714.585 677.0193) 
(list 640.5625 677.2693)))
(apply 'command (append '("pline") coords '("c")))
(setq currobj (ssadd (entlast) currobj))
(setq coords (list 
(list 640.5625 677.4123) 
(list 714.585 677.1623) 
(list 714.585 677.3393) 
(list 640.5625 677.4893)))
(apply 'command (append '("pline") coords '("c")))
(setq currobj (ssadd (entlast) currobj))
(setq coords (list 
(list 640.5625 677.6323) 
(list 714.585 677.4823) 
(list 714.585 677.6593) 
(list 640.5625 677.7093)))
(apply 'command (append '("pline") coords '("c")))
(setq currobj (ssadd (entlast) currobj))
(setq coords (list 
(list 640.5625 677.8523) 
(list 714.585 677.8023) 
(list 714.585 677.9793) 
(list 640.5625 677.9293)))
(apply 'command (append '("pline") coords '("c")))
(setq currobj (ssadd (entlast) currobj))
(setq coords (list 
(list 640.5625 678.0723) 
(list 714.585 678.1223) 
(list 714.585 678.2993) 
(list 640.5625 678.1493)))
(apply 'command (append '("pline") coords '("c")))
(setq currobj (ssadd (entlast) currobj))
(setq coords (list 
(list 640.5625 678.2923) 
(list 714.585 678.4423) 
(list 714.585 678.6193) 
(list 640.5625 678.3693)))
(apply 'command (append '("pline") coords '("c")))
(setq currobj (ssadd (entlast) currobj))
(setq coords (list 
(list 640.5625 678.5123) 
(list 714.585 678.7623) 
(list 714.585 678.9393) 
(list 640.5625 678.5893)))
(apply 'command (append '("pline") coords '("c")))
(setq currobj (ssadd (entlast) currobj))
(setq coords (list 
(list 640.5625 678.7323) 
(list 714.585 679.0823) 
(list 714.585 679.2593) 
(list 640.5625 678.8093)))
(apply 'command (append '("pline") coords '("c")))
(setq currobj (ssadd (entlast) currobj))
(setq coords (list 
(list 640.5625 678.9523) 
(list 714.585 679.4023) 
(list 714.585 679.5793) 
(list 640.5625 679.0293)))
(apply 'command (append '("pline") coords '("c")))
(setq currobj (ssadd (entlast) currobj))
(setq coords (list 
(list 640.5625 679.1723) 
(list 714.585 679.7223) 
(list 714.585 679.8993) 
(list 640.5625 679.2493)))
(apply 'command (append '("pline") coords '("c")))
(setq currobj (ssadd (entlast) currobj))
(setq coords (list 
(list 640.5625 679.3923) 
(list 714.585 680.0423) 
(list 714.585 680.2193) 
(list 640.5625 679.4693)))
(apply 'command (append '("pline") coords '("c")))
(setq currobj (ssadd (entlast) currobj))
(setq coords (list 
(list 639.4375 679.4693) 
(list 565.415 680.2193) 
(list 565.415 680.0423) 
(list 639.4375 679.3923)))
(apply 'command (append '("pline") coords '("c")))
(setq currobj (ssadd (entlast) currobj))
(setq coords (list 
(list 639.4375 679.2493) 
(list 565.415 679.8993) 
(list 565.415 679.7223) 
(list 639.4375 679.1723)))
(apply 'command (append '("pline") coords '("c")))
(setq currobj (ssadd (entlast) currobj))
(setq coords (list 
(list 639.4375 679.0293) 
(list 565.415 679.5793) 
(list 565.415 679.4023) 
(list 639.4375 678.9523)))
(apply 'command (append '("pline") coords '("c")))
(setq currobj (ssadd (entlast) currobj))
(setq coords (list 
(list 639.4375 678.8093) 
(list 565.415 679.2593) 
(list 565.415 679.0823) 
(list 639.4375 678.7323)))
(apply 'command (append '("pline") coords '("c")))
(setq currobj (ssadd (entlast) currobj))
(setq coords (list 
(list 639.4375 678.5893) 
(list 565.415 678.9393) 
(list 565.415 678.7623) 
(list 639.4375 678.5123)))
(apply 'command (append '("pline") coords '("c")))
(setq currobj (ssadd (entlast) currobj))
(setq coords (list 
(list 639.4375 678.3693) 
(list 565.415 678.6193) 
(list 565.415 678.4423) 
(list 639.4375 678.2923)))
(apply 'command (append '("pline") coords '("c")))
(setq currobj (ssadd (entlast) currobj))
(setq coords (list 
(list 639.4375 678.1493) 
(list 565.415 678.2993) 
(list 565.415 678.1223) 
(list 639.4375 678.0723)))
(apply 'command (append '("pline") coords '("c")))
(setq currobj (ssadd (entlast) currobj))
(setq coords (list 
(list 639.4375 677.9293) 
(list 565.415 677.9793) 
(list 565.415 677.8023) 
(list 639.4375 677.8523)))
(apply 'command (append '("pline") coords '("c")))
(setq currobj (ssadd (entlast) currobj))
(setq coords (list 
(list 639.4375 677.7093) 
(list 565.415 677.6593) 
(list 565.415 677.4823) 
(list 639.4375 677.6323)))
(apply 'command (append '("pline") coords '("c")))
(setq currobj (ssadd (entlast) currobj))
(setq coords (list 
(list 639.4375 677.4893) 
(list 565.415 677.3393) 
(list 565.415 677.1623) 
(list 639.4375 677.4123)))
(apply 'command (append '("pline") coords '("c")))
(setq currobj (ssadd (entlast) currobj))
(setq coords (list 
(list 639.4375 677.2693) 
(list 565.415 677.0193) 
(list 565.415 676.8423) 
(list 639.4375 677.1923)))
(apply 'command (append '("pline") coords '("c")))
(setq currobj (ssadd (entlast) currobj))
(setq coords (list 
(list 639.4375 677.0493) 
(list 565.415 676.6993) 
(list 565.415 676.5223) 
(list 639.4375 676.9723)))
(apply 'command (append '("pline") coords '("c")))
(setq currobj (ssadd (entlast) currobj))
(setq coords (list 
(list 639.4375 676.8293) 
(list 565.415 676.3793) 
(list 565.415 676.2023) 
(list 639.4375 676.7523)))
(apply 'command (append '("pline") coords '("c")))
(setq currobj (ssadd (entlast) currobj))
(setq coords (list 
(list 639.4375 676.6093) 
(list 565.415 676.0593) 
(list 565.415 675.8823) 
(list 639.4375 676.5323)))
(apply 'command (append '("pline") coords '("c")))
(setq currobj (ssadd (entlast) currobj))
(setq coords (list 
(list 639.4375 676.3893) 
(list 565.415 675.7393) 
(list 565.415 675.5623) 
(list 639.4375 676.3123)))
(apply 'command (append '("pline") coords '("c")))
(setq currobj (ssadd (entlast) currobj))
(command "_layer" "set" "nitride" "")
(command "_layer" "set" "text" "")
(command "_circle" "639.0625,665.1693" "0.075")
(command "_circle" "639.0625,665.4693" "0.075")
(command "_circle" "639.0625,665.7693" "0.075")
(command "_circle" "639.0625,666.0693" "0.075")
(command "_circle" "639.0625,666.3693" "0.075")
(command "_circle" "638.7625,665.1693" "0.075")
(command "_circle" "638.7625,665.4693" "0.075")
(command "_circle" "638.7625,665.7693" "0.075")
(command "_circle" "638.7625,666.0693" "0.075")
(command "_circle" "638.7625,666.3693" "0.075")
(command "_circle" "638.4625,665.1693" "0.075")
(command "_circle" "638.4625,665.4693" "0.075")
(command "_circle" "638.4625,665.7693" "0.075")
(command "_circle" "638.4625,666.0693" "0.075")
(command "_circle" "638.4625,666.3693" "0.075")
(command "_circle" "638.1625,665.1693" "0.075")
(command "_circle" "638.1625,665.4693" "0.075")
(command "_circle" "638.1625,665.7693" "0.075")
(command "_circle" "638.1625,666.0693" "0.075")
(command "_circle" "638.1625,666.3693" "0.075")
(command "_circle" "637.8625,665.1693" "0.075")
(command "_circle" "637.8625,665.4693" "0.075")
(command "_circle" "637.8625,665.7693" "0.075")
(command "_circle" "637.8625,666.0693" "0.075")
(command "_circle" "637.8625,666.3693" "0.075")
(command "_layer" "set" "nitride" "")
(setq coords (list 
(list 640.2625 690.6123) 
(list 640.2625 806.257) 
(list 639.7375 806.257) 
(list 639.7375 690.6123)))
(apply 'command (append '("pline") coords '("c")))
(setq currobj (ssadd (entlast) currobj))
(command "_layer" "set" "prebias" "")
(command "_rectangle" "639.7375,690.6123" "640.2625,806.257")
(setq currobj (ssadd (entlast) currobj))
(command "_layer" "set" "nitride" "")
(setq coords (list 
(list 640.2625 806.257) 
(list 640.5625 816.257) 
(list 640.5625 816.257) 
(list 640.5625 817.257) 
(list 714.585 816.507) 
(list 714.585 821.45) 
(list 640.5625 820.7) 
(list 640.5625 821.7) 
(list 640.5625 821.7) 
(list 640.2625 831.7) 
(list 639.7375 831.7) 
(list 639.4375 821.7) 
(list 639.4375 821.7) 
(list 639.4375 820.7) 
(list 565.415 821.45) 
(list 565.415 816.507) 
(list 639.4375 817.257) 
(list 639.4375 816.257) 
(list 639.4375 816.257) 
(list 639.7375 806.257)))
(apply 'command (append '("pline") coords '("c")))
(setq currobj (ssadd (entlast) currobj))
(command "_layer" "set" "prebias" "")
(setq coords (list 
(list 639.4375 806.257) 
(list 639.4375 817.257) 
(list 565.415 816.507) 
(list 565.415 821.45) 
(list 639.4375 820.7) 
(list 639.4375 831.7) 
(list 640.5625 831.7) 
(list 640.5625 820.7) 
(list 714.585 821.45) 
(list 714.585 816.507) 
(list 640.5625 817.257) 
(list 640.5625 806.257)))
(apply 'command (append '("pline") coords '("c")))
(setq currobj (ssadd (entlast) currobj))
(command "_layer" "set" "nitride" "")
(command "_layer" "set" "fda1" "")
(setq coords (list 
(list 640.5625 817.4) 
(list 714.585 816.65) 
(list 714.585 816.827) 
(list 640.5625 817.477)))
(apply 'command (append '("pline") coords '("c")))
(setq currobj (ssadd (entlast) currobj))
(setq coords (list 
(list 640.5625 817.62) 
(list 714.585 816.97) 
(list 714.585 817.147) 
(list 640.5625 817.697)))
(apply 'command (append '("pline") coords '("c")))
(setq currobj (ssadd (entlast) currobj))
(setq coords (list 
(list 640.5625 817.84) 
(list 714.585 817.29) 
(list 714.585 817.467) 
(list 640.5625 817.917)))
(apply 'command (append '("pline") coords '("c")))
(setq currobj (ssadd (entlast) currobj))
(setq coords (list 
(list 640.5625 818.06) 
(list 714.585 817.61) 
(list 714.585 817.787) 
(list 640.5625 818.137)))
(apply 'command (append '("pline") coords '("c")))
(setq currobj (ssadd (entlast) currobj))
(setq coords (list 
(list 640.5625 818.28) 
(list 714.585 817.93) 
(list 714.585 818.107) 
(list 640.5625 818.357)))
(apply 'command (append '("pline") coords '("c")))
(setq currobj (ssadd (entlast) currobj))
(setq coords (list 
(list 640.5625 818.5) 
(list 714.585 818.25) 
(list 714.585 818.427) 
(list 640.5625 818.577)))
(apply 'command (append '("pline") coords '("c")))
(setq currobj (ssadd (entlast) currobj))
(setq coords (list 
(list 640.5625 818.72) 
(list 714.585 818.57) 
(list 714.585 818.747) 
(list 640.5625 818.797)))
(apply 'command (append '("pline") coords '("c")))
(setq currobj (ssadd (entlast) currobj))
(setq coords (list 
(list 640.5625 818.94) 
(list 714.585 818.89) 
(list 714.585 819.067) 
(list 640.5625 819.017)))
(apply 'command (append '("pline") coords '("c")))
(setq currobj (ssadd (entlast) currobj))
(setq coords (list 
(list 640.5625 819.16) 
(list 714.585 819.21) 
(list 714.585 819.387) 
(list 640.5625 819.237)))
(apply 'command (append '("pline") coords '("c")))
(setq currobj (ssadd (entlast) currobj))
(setq coords (list 
(list 640.5625 819.38) 
(list 714.585 819.53) 
(list 714.585 819.707) 
(list 640.5625 819.457)))
(apply 'command (append '("pline") coords '("c")))
(setq currobj (ssadd (entlast) currobj))
(setq coords (list 
(list 640.5625 819.6) 
(list 714.585 819.85) 
(list 714.585 820.027) 
(list 640.5625 819.677)))
(apply 'command (append '("pline") coords '("c")))
(setq currobj (ssadd (entlast) currobj))
(setq coords (list 
(list 640.5625 819.82) 
(list 714.585 820.17) 
(list 714.585 820.347) 
(list 640.5625 819.897)))
(apply 'command (append '("pline") coords '("c")))
(setq currobj (ssadd (entlast) currobj))
(setq coords (list 
(list 640.5625 820.04) 
(list 714.585 820.49) 
(list 714.585 820.667) 
(list 640.5625 820.117)))
(apply 'command (append '("pline") coords '("c")))
(setq currobj (ssadd (entlast) currobj))
(setq coords (list 
(list 640.5625 820.26) 
(list 714.585 820.81) 
(list 714.585 820.987) 
(list 640.5625 820.337)))
(apply 'command (append '("pline") coords '("c")))
(setq currobj (ssadd (entlast) currobj))
(setq coords (list 
(list 640.5625 820.48) 
(list 714.585 821.13) 
(list 714.585 821.307) 
(list 640.5625 820.557)))
(apply 'command (append '("pline") coords '("c")))
(setq currobj (ssadd (entlast) currobj))
(setq coords (list 
(list 639.4375 820.557) 
(list 565.415 821.307) 
(list 565.415 821.13) 
(list 639.4375 820.48)))
(apply 'command (append '("pline") coords '("c")))
(setq currobj (ssadd (entlast) currobj))
(setq coords (list 
(list 639.4375 820.337) 
(list 565.415 820.987) 
(list 565.415 820.81) 
(list 639.4375 820.26)))
(apply 'command (append '("pline") coords '("c")))
(setq currobj (ssadd (entlast) currobj))
(setq coords (list 
(list 639.4375 820.117) 
(list 565.415 820.667) 
(list 565.415 820.49) 
(list 639.4375 820.04)))
(apply 'command (append '("pline") coords '("c")))
(setq currobj (ssadd (entlast) currobj))
(setq coords (list 
(list 639.4375 819.897) 
(list 565.415 820.347) 
(list 565.415 820.17) 
(list 639.4375 819.82)))
(apply 'command (append '("pline") coords '("c")))
(setq currobj (ssadd (entlast) currobj))
(setq coords (list 
(list 639.4375 819.677) 
(list 565.415 820.027) 
(list 565.415 819.85) 
(list 639.4375 819.6)))
(apply 'command (append '("pline") coords '("c")))
(setq currobj (ssadd (entlast) currobj))
(setq coords (list 
(list 639.4375 819.457) 
(list 565.415 819.707) 
(list 565.415 819.53) 
(list 639.4375 819.38)))
(apply 'command (append '("pline") coords '("c")))
(setq currobj (ssadd (entlast) currobj))
(setq coords (list 
(list 639.4375 819.237) 
(list 565.415 819.387) 
(list 565.415 819.21) 
(list 639.4375 819.16)))
(apply 'command (append '("pline") coords '("c")))
(setq currobj (ssadd (entlast) currobj))
(setq coords (list 
(list 639.4375 819.017) 
(list 565.415 819.067) 
(list 565.415 818.89) 
(list 639.4375 818.94)))
(apply 'command (append '("pline") coords '("c")))
(setq currobj (ssadd (entlast) currobj))
(setq coords (list 
(list 639.4375 818.797) 
(list 565.415 818.747) 
(list 565.415 818.57) 
(list 639.4375 818.72)))
(apply 'command (append '("pline") coords '("c")))
(setq currobj (ssadd (entlast) currobj))
(setq coords (list 
(list 639.4375 818.577) 
(list 565.415 818.427) 
(list 565.415 818.25) 
(list 639.4375 818.5)))
(apply 'command (append '("pline") coords '("c")))
(setq currobj (ssadd (entlast) currobj))
(setq coords (list 
(list 639.4375 818.357) 
(list 565.415 818.107) 
(list 565.415 817.93) 
(list 639.4375 818.28)))
(apply 'command (append '("pline") coords '("c")))
(setq currobj (ssadd (entlast) currobj))
(setq coords (list 
(list 639.4375 818.137) 
(list 565.415 817.787) 
(list 565.415 817.61) 
(list 639.4375 818.06)))
(apply 'command (append '("pline") coords '("c")))
(setq currobj (ssadd (entlast) currobj))
(setq coords (list 
(list 639.4375 817.917) 
(list 565.415 817.467) 
(list 565.415 817.29) 
(list 639.4375 817.84)))
(apply 'command (append '("pline") coords '("c")))
(setq currobj (ssadd (entlast) currobj))
(setq coords (list 
(list 639.4375 817.697) 
(list 565.415 817.147) 
(list 565.415 816.97) 
(list 639.4375 817.62)))
(apply 'command (append '("pline") coords '("c")))
(setq currobj (ssadd (entlast) currobj))
(setq coords (list 
(list 639.4375 817.477) 
(list 565.415 816.827) 
(list 565.415 816.65) 
(list 639.4375 817.4)))
(apply 'command (append '("pline") coords '("c")))
(setq currobj (ssadd (entlast) currobj))
(command "_layer" "set" "nitride" "")
(command "_layer" "set" "text" "")
(command "_circle" "639.0625,806.257" "0.075")
(command "_circle" "639.0625,806.557" "0.075")
(command "_circle" "639.0625,806.857" "0.075")
(command "_circle" "639.0625,807.157" "0.075")
(command "_circle" "639.0625,807.457" "0.075")
(command "_circle" "638.7625,806.257" "0.075")
(command "_circle" "638.7625,806.557" "0.075")
(command "_circle" "638.7625,806.857" "0.075")
(command "_circle" "638.7625,807.157" "0.075")
(command "_circle" "638.7625,807.457" "0.075")
(command "_circle" "638.4625,806.257" "0.075")
(command "_circle" "638.4625,806.557" "0.075")
(command "_circle" "638.4625,806.857" "0.075")
(command "_circle" "638.4625,807.157" "0.075")
(command "_circle" "638.4625,807.457" "0.075")
(command "_circle" "638.1625,806.257" "0.075")
(command "_circle" "638.1625,806.557" "0.075")
(command "_circle" "638.1625,806.857" "0.075")
(command "_circle" "638.1625,807.157" "0.075")
(command "_circle" "638.1625,807.457" "0.075")
(command "_circle" "637.8625,806.257" "0.075")
(command "_circle" "637.8625,806.557" "0.075")
(command "_circle" "637.8625,806.857" "0.075")
(command "_circle" "637.8625,807.157" "0.075")
(command "_circle" "637.8625,807.457" "0.075")
(command "_layer" "set" "nitride" "")
(setq coords (list 
(list 640.2625 831.7) 
(list 640.2625 836.7) 
(list 639.7375 836.7) 
(list 639.7375 831.7)))
(apply 'command (append '("pline") coords '("c")))
(setq currobj (ssadd (entlast) currobj))
(command "_layer" "set" "prebias" "")
(command "_rectangle" "639.7375,831.7" "640.2625,836.7")
(setq currobj (ssadd (entlast) currobj))
(command "_layer" "set" "nitride" "")
(setq cooledsinglenanobeam2 currobj)
(setq currobj nil)
(setq currobj (ssadd))
; DRAWING PHOTONIC CRYSTAL
(command "_layer" "set" "negYjunc" "")
(setq coords (list 
(list 640.125 866.7) 
(list 640 851.7) 
(list 640 866.7)))
(apply 'command (append '("pline") coords '("c")))
(setq currobj (ssadd (entlast) currobj))
(setq coords (list 
(list 640.2625 836.7) 
(list 640.405 866.7) 
(list 641.092 866.7) 
(list 641.092 836.7)))
(apply 'command (append '("pline") coords '("c")))
(setq currobj (ssadd (entlast) currobj))
(setq coords (list 
(list 639.875 866.7) 
(list 640 851.7) 
(list 640 866.7)))
(apply 'command (append '("pline") coords '("c")))
(setq currobj (ssadd (entlast) currobj))
(setq coords (list 
(list 639.7375 836.7) 
(list 639.595 866.7) 
(list 638.908 866.7) 
(list 638.908 836.7)))
(apply 'command (append '("pline") coords '("c")))
(setq currobj (ssadd (entlast) currobj))
(command "_layer" "set" "nitride" "")
(setq yjunction2 currobj)
(setq currobj nil)
(setq currobj (ssadd))
(setq tap2 nil)
(setq tap2 (ssadd))
(command "_layer" "set" "phc" "")
(setq coords (list 
(list 640 866.7) 
(list 640.125 866.7) 
(list 640.125 866.7103) 
(list 640.125 866.7206) 
(list 640.125 866.7308) 
(list 640.125 866.7411) 
(list 640.125 866.7514) 
(list 640.125 866.7617) 
(list 640.125 866.7719) 
(list 640.125 866.7822) 
(list 640.125 866.7925) 
(list 640.125 866.8028) 
(list 640.125 866.8131) 
(list 640.125 866.8233) 
(list 640.125 866.8336) 
(list 640.125 866.8439) 
(list 640.125 866.8542) 
(list 640.125 866.8644) 
(list 640.125 866.8747) 
(list 640.125 866.885) 
(list 640.125 866.8953) 
(list 640.125 866.9056) 
(list 640.125 866.9158) 
(list 640.125 866.9261) 
(list 640.125 866.9364) 
(list 640.125 866.9467) 
(list 640.125 866.9569) 
(list 640.125 866.9672) 
(list 640.125 866.9775) 
(list 640.125 866.9878) 
(list 640.125 866.9981) 
(list 640.125 867.0083) 
(list 640.125 867.0186) 
(list 640.125 867.0289) 
(list 640.125 867.0392) 
(list 640.125 867.0494) 
(list 640.125 867.0597) 
(list 640.125 867.07) 
(list 640 867.07)))
(apply 'command (append '("pline") coords '("c")))
(setq tap2 (ssadd (entlast) tap2))
(command "_mirror" (entlast) "" "640,900" "640,901" "No")
(setq tap2 (ssadd (entlast) tap2))
(setq coords (list 
(list 640.4144 866.7) 
(list 640.405 866.7) 
(list 640.4053 866.7103) 
(list 640.4055 866.7206) 
(list 640.4057 866.7308) 
(list 640.4058 866.7411) 
(list 640.4059 866.7514) 
(list 640.4058 866.7617) 
(list 640.4057 866.7719) 
(list 640.4055 866.7822) 
(list 640.4052 866.7925) 
(list 640.4047 866.8028) 
(list 640.4043 866.8131) 
(list 640.4037 866.8233) 
(list 640.4032 866.8336) 
(list 640.4026 866.8439) 
(list 640.4021 866.8542) 
(list 640.4016 866.8644) 
(list 640.4012 866.8747) 
(list 640.4009 866.885) 
(list 640.4007 866.8953) 
(list 640.4007 866.9056) 
(list 640.4009 866.9158) 
(list 640.4012 866.9261) 
(list 640.4018 866.9364) 
(list 640.4025 866.9467) 
(list 640.4033 866.9569) 
(list 640.4043 866.9672) 
(list 640.4054 866.9775) 
(list 640.4067 866.9878) 
(list 640.4079 866.9981) 
(list 640.4092 867.0083) 
(list 640.4104 867.0186) 
(list 640.4115 867.0289) 
(list 640.4125 867.0392) 
(list 640.4134 867.0494) 
(list 640.414 867.0597) 
(list 640.4144 867.07) 
(list 640.4144 867.07)))
(apply 'command (append '("pline") coords '("c")))
(setq tap2 (ssadd (entlast) tap2))
(command "_mirror" (entlast) "" "640,900" "640,901" "No")
(setq tap2 (ssadd (entlast) tap2))
(setq coords (list 
(list 641.092 866.7) 
(list 640.4144 866.7) 
(list 640.4144 866.7103) 
(list 640.4144 866.7206) 
(list 640.4144 866.7308) 
(list 640.4144 866.7411) 
(list 640.4144 866.7514) 
(list 640.4144 866.7617) 
(list 640.4144 866.7719) 
(list 640.4144 866.7822) 
(list 640.4144 866.7925) 
(list 640.4144 866.8028) 
(list 640.4144 866.8131) 
(list 640.4144 866.8233) 
(list 640.4144 866.8336) 
(list 640.4144 866.8439) 
(list 640.4144 866.8542) 
(list 640.4144 866.8644) 
(list 640.4144 866.8747) 
(list 640.4144 866.885) 
(list 640.4144 866.8953) 
(list 640.4144 866.9056) 
(list 640.4144 866.9158) 
(list 640.4144 866.9261) 
(list 640.4144 866.9364) 
(list 640.4144 866.9467) 
(list 640.4144 866.9569) 
(list 640.4144 866.9672) 
(list 640.4144 866.9775) 
(list 640.4144 866.9878) 
(list 640.4144 866.9981) 
(list 640.4144 867.0083) 
(list 640.4144 867.0186) 
(list 640.4144 867.0289) 
(list 640.4144 867.0392) 
(list 640.4144 867.0494) 
(list 640.4144 867.0597) 
(list 640.4144 867.07) 
(list 641.092 867.07)))
(apply 'command (append '("pline") coords '("c")))
(setq tap2 (ssadd (entlast) tap2))
(command "_mirror" (entlast) "" "640,900" "640,901" "No")
(setq tap2 (ssadd (entlast) tap2))
(setq coords (list 
(list 640 867.07) 
(list 640.125 867.07) 
(list 640.125 867.0803) 
(list 640.125 867.0906) 
(list 640.125 867.1008) 
(list 640.125 867.1111) 
(list 640.125 867.1214) 
(list 640.125 867.1317) 
(list 640.125 867.1419) 
(list 640.125 867.1522) 
(list 640.125 867.1625) 
(list 640.125 867.1728) 
(list 640.125 867.1831) 
(list 640.125 867.1933) 
(list 640.125 867.2036) 
(list 640.125 867.2139) 
(list 640.125 867.2242) 
(list 640.125 867.2344) 
(list 640.125 867.2447) 
(list 640.125 867.255) 
(list 640.125 867.2653) 
(list 640.125 867.2756) 
(list 640.125 867.2858) 
(list 640.125 867.2961) 
(list 640.125 867.3064) 
(list 640.125 867.3167) 
(list 640.125 867.3269) 
(list 640.125 867.3372) 
(list 640.125 867.3475) 
(list 640.125 867.3578) 
(list 640.125 867.3681) 
(list 640.125 867.3783) 
(list 640.125 867.3886) 
(list 640.125 867.3989) 
(list 640.125 867.4092) 
(list 640.125 867.4194) 
(list 640.125 867.4297) 
(list 640.125 867.44) 
(list 640 867.44)))
(apply 'command (append '("pline") coords '("c")))
(setq tap2 (ssadd (entlast) tap2))
(command "_mirror" (entlast) "" "640,900" "640,901" "No")
(setq tap2 (ssadd (entlast) tap2))
(setq coords (list 
(list 640.4238 867.07) 
(list 640.4144 867.07) 
(list 640.4145 867.0803) 
(list 640.4144 867.0906) 
(list 640.4139 867.1008) 
(list 640.4132 867.1111) 
(list 640.4121 867.1214) 
(list 640.4108 867.1317) 
(list 640.4093 867.1419) 
(list 640.4076 867.1522) 
(list 640.4058 867.1625) 
(list 640.4038 867.1728) 
(list 640.4019 867.1831) 
(list 640.3999 867.1933) 
(list 640.3981 867.2036) 
(list 640.3965 867.2139) 
(list 640.3951 867.2242) 
(list 640.3939 867.2344) 
(list 640.3931 867.2447) 
(list 640.3927 867.255) 
(list 640.3927 867.2653) 
(list 640.3931 867.2756) 
(list 640.3939 867.2858) 
(list 640.3951 867.2961) 
(list 640.3967 867.3064) 
(list 640.3987 867.3167) 
(list 640.4009 867.3269) 
(list 640.4034 867.3372) 
(list 640.4061 867.3475) 
(list 640.4088 867.3578) 
(list 640.4115 867.3681) 
(list 640.4142 867.3783) 
(list 640.4166 867.3886) 
(list 640.4189 867.3989) 
(list 640.4208 867.4092) 
(list 640.4222 867.4194) 
(list 640.4233 867.4297) 
(list 640.4238 867.44) 
(list 640.4238 867.44)))
(apply 'command (append '("pline") coords '("c")))
(setq tap2 (ssadd (entlast) tap2))
(command "_mirror" (entlast) "" "640,900" "640,901" "No")
(setq tap2 (ssadd (entlast) tap2))
(setq coords (list 
(list 641.092 867.07) 
(list 640.4238 867.07) 
(list 640.4238 867.0803) 
(list 640.4238 867.0906) 
(list 640.4238 867.1008) 
(list 640.4238 867.1111) 
(list 640.4238 867.1214) 
(list 640.4238 867.1317) 
(list 640.4238 867.1419) 
(list 640.4238 867.1522) 
(list 640.4238 867.1625) 
(list 640.4238 867.1728) 
(list 640.4238 867.1831) 
(list 640.4238 867.1933) 
(list 640.4238 867.2036) 
(list 640.4238 867.2139) 
(list 640.4238 867.2242) 
(list 640.4238 867.2344) 
(list 640.4238 867.2447) 
(list 640.4238 867.255) 
(list 640.4238 867.2653) 
(list 640.4238 867.2756) 
(list 640.4238 867.2858) 
(list 640.4238 867.2961) 
(list 640.4238 867.3064) 
(list 640.4238 867.3167) 
(list 640.4238 867.3269) 
(list 640.4238 867.3372) 
(list 640.4238 867.3475) 
(list 640.4238 867.3578) 
(list 640.4238 867.3681) 
(list 640.4238 867.3783) 
(list 640.4238 867.3886) 
(list 640.4238 867.3989) 
(list 640.4238 867.4092) 
(list 640.4238 867.4194) 
(list 640.4238 867.4297) 
(list 640.4238 867.44) 
(list 641.092 867.44)))
(apply 'command (append '("pline") coords '("c")))
(setq tap2 (ssadd (entlast) tap2))
(command "_mirror" (entlast) "" "640,900" "640,901" "No")
(setq tap2 (ssadd (entlast) tap2))
(setq coords (list 
(list 640 867.44) 
(list 640.125 867.44) 
(list 640.125 867.4503) 
(list 640.125 867.4606) 
(list 640.125 867.4708) 
(list 640.125 867.4811) 
(list 640.125 867.4914) 
(list 640.125 867.5017) 
(list 640.125 867.5119) 
(list 640.125 867.5222) 
(list 640.125 867.5325) 
(list 640.125 867.5428) 
(list 640.125 867.5531) 
(list 640.125 867.5633) 
(list 640.125 867.5736) 
(list 640.125 867.5839) 
(list 640.125 867.5942) 
(list 640.125 867.6044) 
(list 640.125 867.6147) 
(list 640.125 867.625) 
(list 640.125 867.6353) 
(list 640.125 867.6456) 
(list 640.125 867.6558) 
(list 640.125 867.6661) 
(list 640.125 867.6764) 
(list 640.125 867.6867) 
(list 640.125 867.6969) 
(list 640.125 867.7072) 
(list 640.125 867.7175) 
(list 640.125 867.7278) 
(list 640.125 867.7381) 
(list 640.125 867.7483) 
(list 640.125 867.7586) 
(list 640.125 867.7689) 
(list 640.125 867.7792) 
(list 640.125 867.7894) 
(list 640.125 867.7997) 
(list 640.125 867.81) 
(list 640 867.81)))
(apply 'command (append '("pline") coords '("c")))
(setq tap2 (ssadd (entlast) tap2))
(command "_mirror" (entlast) "" "640,900" "640,901" "No")
(setq tap2 (ssadd (entlast) tap2))
(setq coords (list 
(list 640.4332 867.44) 
(list 640.4238 867.44) 
(list 640.4238 867.4503) 
(list 640.4232 867.4606) 
(list 640.4221 867.4708) 
(list 640.4205 867.4811) 
(list 640.4184 867.4914) 
(list 640.4158 867.5017) 
(list 640.4129 867.5119) 
(list 640.4097 867.5222) 
(list 640.4063 867.5325) 
(list 640.4029 867.5428) 
(list 640.3994 867.5531) 
(list 640.3961 867.5633) 
(list 640.3931 867.5736) 
(list 640.3903 867.5839) 
(list 640.388 867.5942) 
(list 640.3863 867.6044) 
(list 640.3851 867.6147) 
(list 640.3845 867.625) 
(list 640.3846 867.6353) 
(list 640.3854 867.6456) 
(list 640.3869 867.6558) 
(list 640.389 867.6661) 
(list 640.3917 867.6764) 
(list 640.3949 867.6867) 
(list 640.3985 867.6969) 
(list 640.4025 867.7072) 
(list 640.4067 867.7175) 
(list 640.4109 867.7278) 
(list 640.4151 867.7381) 
(list 640.4192 867.7483) 
(list 640.4229 867.7586) 
(list 640.4262 867.7689) 
(list 640.429 867.7792) 
(list 640.4311 867.7894) 
(list 640.4325 867.7997) 
(list 640.4332 867.81) 
(list 640.4332 867.81)))
(apply 'command (append '("pline") coords '("c")))
(setq tap2 (ssadd (entlast) tap2))
(command "_mirror" (entlast) "" "640,900" "640,901" "No")
(setq tap2 (ssadd (entlast) tap2))
(setq coords (list 
(list 641.092 867.44) 
(list 640.4332 867.44) 
(list 640.4332 867.4503) 
(list 640.4332 867.4606) 
(list 640.4332 867.4708) 
(list 640.4332 867.4811) 
(list 640.4332 867.4914) 
(list 640.4332 867.5017) 
(list 640.4332 867.5119) 
(list 640.4332 867.5222) 
(list 640.4332 867.5325) 
(list 640.4332 867.5428) 
(list 640.4332 867.5531) 
(list 640.4332 867.5633) 
(list 640.4332 867.5736) 
(list 640.4332 867.5839) 
(list 640.4332 867.5942) 
(list 640.4332 867.6044) 
(list 640.4332 867.6147) 
(list 640.4332 867.625) 
(list 640.4332 867.6353) 
(list 640.4332 867.6456) 
(list 640.4332 867.6558) 
(list 640.4332 867.6661) 
(list 640.4332 867.6764) 
(list 640.4332 867.6867) 
(list 640.4332 867.6969) 
(list 640.4332 867.7072) 
(list 640.4332 867.7175) 
(list 640.4332 867.7278) 
(list 640.4332 867.7381) 
(list 640.4332 867.7483) 
(list 640.4332 867.7586) 
(list 640.4332 867.7689) 
(list 640.4332 867.7792) 
(list 640.4332 867.7894) 
(list 640.4332 867.7997) 
(list 640.4332 867.81) 
(list 641.092 867.81)))
(apply 'command (append '("pline") coords '("c")))
(setq tap2 (ssadd (entlast) tap2))
(command "_mirror" (entlast) "" "640,900" "640,901" "No")
(setq tap2 (ssadd (entlast) tap2))
(setq coords (list 
(list 640 867.81) 
(list 640.125 867.81) 
(list 640.125 867.8203) 
(list 640.125 867.8306) 
(list 640.125 867.8408) 
(list 640.125 867.8511) 
(list 640.125 867.8614) 
(list 640.125 867.8717) 
(list 640.125 867.8819) 
(list 640.125 867.8922) 
(list 640.125 867.9025) 
(list 640.125 867.9128) 
(list 640.125 867.9231) 
(list 640.125 867.9333) 
(list 640.125 867.9436) 
(list 640.125 867.9539) 
(list 640.125 867.9642) 
(list 640.125 867.9744) 
(list 640.125 867.9847) 
(list 640.125 867.995) 
(list 640.125 868.0053) 
(list 640.125 868.0156) 
(list 640.125 868.0258) 
(list 640.125 868.0361) 
(list 640.125 868.0464) 
(list 640.125 868.0567) 
(list 640.125 868.0669) 
(list 640.125 868.0772) 
(list 640.125 868.0875) 
(list 640.125 868.0978) 
(list 640.125 868.1081) 
(list 640.125 868.1183) 
(list 640.125 868.1286) 
(list 640.125 868.1389) 
(list 640.125 868.1492) 
(list 640.125 868.1594) 
(list 640.125 868.1697) 
(list 640.125 868.18) 
(list 640 868.18)))
(apply 'command (append '("pline") coords '("c")))
(setq tap2 (ssadd (entlast) tap2))
(command "_mirror" (entlast) "" "640,900" "640,901" "No")
(setq tap2 (ssadd (entlast) tap2))
(setq coords (list 
(list 640.4426 867.81) 
(list 640.4332 867.81) 
(list 640.4331 867.8203) 
(list 640.4321 867.8306) 
(list 640.4303 867.8408) 
(list 640.4278 867.8511) 
(list 640.4246 867.8614) 
(list 640.4208 867.8717) 
(list 640.4165 867.8819) 
(list 640.4119 867.8922) 
(list 640.407 867.9025) 
(list 640.402 867.9128) 
(list 640.397 867.9231) 
(list 640.3923 867.9333) 
(list 640.388 867.9436) 
(list 640.3842 867.9539) 
(list 640.381 867.9642) 
(list 640.3786 867.9744) 
(list 640.377 867.9847) 
(list 640.3763 867.995) 
(list 640.3765 868.0053) 
(list 640.3777 868.0156) 
(list 640.3798 868.0258) 
(list 640.3828 868.0361) 
(list 640.3866 868.0464) 
(list 640.3911 868.0567) 
(list 640.3961 868.0669) 
(list 640.4015 868.0772) 
(list 640.4072 868.0875) 
(list 640.413 868.0978) 
(list 640.4187 868.1081) 
(list 640.4242 868.1183) 
(list 640.4292 868.1286) 
(list 640.4335 868.1389) 
(list 640.4372 868.1492) 
(list 640.44 868.1594) 
(list 640.4418 868.1697) 
(list 640.4426 868.18) 
(list 640.4426 868.18)))
(apply 'command (append '("pline") coords '("c")))
(setq tap2 (ssadd (entlast) tap2))
(command "_mirror" (entlast) "" "640,900" "640,901" "No")
(setq tap2 (ssadd (entlast) tap2))
(setq coords (list 
(list 641.092 867.81) 
(list 640.4426 867.81) 
(list 640.4426 867.8203) 
(list 640.4426 867.8306) 
(list 640.4426 867.8408) 
(list 640.4426 867.8511) 
(list 640.4426 867.8614) 
(list 640.4426 867.8717) 
(list 640.4426 867.8819) 
(list 640.4426 867.8922) 
(list 640.4426 867.9025) 
(list 640.4426 867.9128) 
(list 640.4426 867.9231) 
(list 640.4426 867.9333) 
(list 640.4426 867.9436) 
(list 640.4426 867.9539) 
(list 640.4426 867.9642) 
(list 640.4426 867.9744) 
(list 640.4426 867.9847) 
(list 640.4426 867.995) 
(list 640.4426 868.0053) 
(list 640.4426 868.0156) 
(list 640.4426 868.0258) 
(list 640.4426 868.0361) 
(list 640.4426 868.0464) 
(list 640.4426 868.0567) 
(list 640.4426 868.0669) 
(list 640.4426 868.0772) 
(list 640.4426 868.0875) 
(list 640.4426 868.0978) 
(list 640.4426 868.1081) 
(list 640.4426 868.1183) 
(list 640.4426 868.1286) 
(list 640.4426 868.1389) 
(list 640.4426 868.1492) 
(list 640.4426 868.1594) 
(list 640.4426 868.1697) 
(list 640.4426 868.18) 
(list 641.092 868.18)))
(apply 'command (append '("pline") coords '("c")))
(setq tap2 (ssadd (entlast) tap2))
(command "_mirror" (entlast) "" "640,900" "640,901" "No")
(setq tap2 (ssadd (entlast) tap2))
(setq coords (list 
(list 640 868.18) 
(list 640.125 868.18) 
(list 640.125 868.1903) 
(list 640.125 868.2006) 
(list 640.125 868.2108) 
(list 640.125 868.2211) 
(list 640.125 868.2314) 
(list 640.125 868.2417) 
(list 640.125 868.2519) 
(list 640.125 868.2622) 
(list 640.125 868.2725) 
(list 640.125 868.2828) 
(list 640.125 868.2931) 
(list 640.125 868.3033) 
(list 640.125 868.3136) 
(list 640.125 868.3239) 
(list 640.125 868.3342) 
(list 640.125 868.3444) 
(list 640.125 868.3547) 
(list 640.125 868.365) 
(list 640.125 868.3753) 
(list 640.125 868.3856) 
(list 640.125 868.3958) 
(list 640.125 868.4061) 
(list 640.125 868.4164) 
(list 640.125 868.4267) 
(list 640.125 868.4369) 
(list 640.125 868.4472) 
(list 640.125 868.4575) 
(list 640.125 868.4678) 
(list 640.125 868.4781) 
(list 640.125 868.4883) 
(list 640.125 868.4986) 
(list 640.125 868.5089) 
(list 640.125 868.5192) 
(list 640.125 868.5294) 
(list 640.125 868.5397) 
(list 640.125 868.55) 
(list 640 868.55)))
(apply 'command (append '("pline") coords '("c")))
(setq tap2 (ssadd (entlast) tap2))
(command "_mirror" (entlast) "" "640,900" "640,901" "No")
(setq tap2 (ssadd (entlast) tap2))
(setq coords (list 
(list 640.452 868.18) 
(list 640.4426 868.18) 
(list 640.4423 868.1903) 
(list 640.441 868.2006) 
(list 640.4386 868.2108) 
(list 640.4352 868.2211) 
(list 640.4309 868.2314) 
(list 640.4258 868.2417) 
(list 640.4201 868.2519) 
(list 640.414 868.2622) 
(list 640.4076 868.2725) 
(list 640.401 868.2828) 
(list 640.3946 868.2931) 
(list 640.3885 868.3033) 
(list 640.3829 868.3136) 
(list 640.378 868.3239) 
(list 640.374 868.3342) 
(list 640.3709 868.3444) 
(list 640.3689 868.3547) 
(list 640.3681 868.365) 
(list 640.3685 868.3753) 
(list 640.3701 868.3856) 
(list 640.3728 868.3958) 
(list 640.3767 868.4061) 
(list 640.3815 868.4164) 
(list 640.3873 868.4267) 
(list 640.3937 868.4369) 
(list 640.4006 868.4472) 
(list 640.4079 868.4575) 
(list 640.4152 868.4678) 
(list 640.4223 868.4781) 
(list 640.4292 868.4883) 
(list 640.4354 868.4986) 
(list 640.4409 868.5089) 
(list 640.4454 868.5192) 
(list 640.4489 868.5294) 
(list 640.4511 868.5397) 
(list 640.452 868.55) 
(list 640.452 868.55)))
(apply 'command (append '("pline") coords '("c")))
(setq tap2 (ssadd (entlast) tap2))
(command "_mirror" (entlast) "" "640,900" "640,901" "No")
(setq tap2 (ssadd (entlast) tap2))
(setq coords (list 
(list 641.092 868.18) 
(list 640.452 868.18) 
(list 640.452 868.1903) 
(list 640.452 868.2006) 
(list 640.452 868.2108) 
(list 640.452 868.2211) 
(list 640.452 868.2314) 
(list 640.452 868.2417) 
(list 640.452 868.2519) 
(list 640.452 868.2622) 
(list 640.452 868.2725) 
(list 640.452 868.2828) 
(list 640.452 868.2931) 
(list 640.452 868.3033) 
(list 640.452 868.3136) 
(list 640.452 868.3239) 
(list 640.452 868.3342) 
(list 640.452 868.3444) 
(list 640.452 868.3547) 
(list 640.452 868.365) 
(list 640.452 868.3753) 
(list 640.452 868.3856) 
(list 640.452 868.3958) 
(list 640.452 868.4061) 
(list 640.452 868.4164) 
(list 640.452 868.4267) 
(list 640.452 868.4369) 
(list 640.452 868.4472) 
(list 640.452 868.4575) 
(list 640.452 868.4678) 
(list 640.452 868.4781) 
(list 640.452 868.4883) 
(list 640.452 868.4986) 
(list 640.452 868.5089) 
(list 640.452 868.5192) 
(list 640.452 868.5294) 
(list 640.452 868.5397) 
(list 640.452 868.55) 
(list 641.092 868.55)))
(apply 'command (append '("pline") coords '("c")))
(setq tap2 (ssadd (entlast) tap2))
(command "_mirror" (entlast) "" "640,900" "640,901" "No")
(setq tap2 (ssadd (entlast) tap2))
(setq coords (list 
(list 640 868.55) 
(list 640.125 868.55) 
(list 640.125 868.5603) 
(list 640.125 868.5706) 
(list 640.125 868.5808) 
(list 640.125 868.5911) 
(list 640.125 868.6014) 
(list 640.125 868.6117) 
(list 640.125 868.6219) 
(list 640.125 868.6322) 
(list 640.125 868.6425) 
(list 640.125 868.6528) 
(list 640.125 868.6631) 
(list 640.125 868.6733) 
(list 640.125 868.6836) 
(list 640.125 868.6939) 
(list 640.125 868.7042) 
(list 640.125 868.7144) 
(list 640.125 868.7247) 
(list 640.125 868.735) 
(list 640.125 868.7453) 
(list 640.125 868.7556) 
(list 640.125 868.7658) 
(list 640.125 868.7761) 
(list 640.125 868.7864) 
(list 640.125 868.7967) 
(list 640.125 868.8069) 
(list 640.125 868.8172) 
(list 640.125 868.8275) 
(list 640.125 868.8378) 
(list 640.125 868.8481) 
(list 640.125 868.8583) 
(list 640.125 868.8686) 
(list 640.125 868.8789) 
(list 640.125 868.8892) 
(list 640.125 868.8994) 
(list 640.125 868.9097) 
(list 640.125 868.92) 
(list 640 868.92)))
(apply 'command (append '("pline") coords '("c")))
(setq tap2 (ssadd (entlast) tap2))
(command "_mirror" (entlast) "" "640,900" "640,901" "No")
(setq tap2 (ssadd (entlast) tap2))
(setq coords (list 
(list 640.4614 868.55) 
(list 640.452 868.55) 
(list 640.4516 868.5603) 
(list 640.4498 868.5706) 
(list 640.4468 868.5808) 
(list 640.4425 868.5911) 
(list 640.4372 868.6014) 
(list 640.4308 868.6117) 
(list 640.4238 868.6219) 
(list 640.4161 868.6322) 
(list 640.4081 868.6425) 
(list 640.4001 868.6528) 
(list 640.3922 868.6631) 
(list 640.3847 868.6733) 
(list 640.3779 868.6836) 
(list 640.3719 868.6939) 
(list 640.367 868.7042) 
(list 640.3632 868.7144) 
(list 640.3609 868.7247) 
(list 640.3599 868.735) 
(list 640.3604 868.7453) 
(list 640.3624 868.7556) 
(list 640.3658 868.7658) 
(list 640.3705 868.7761) 
(list 640.3765 868.7864) 
(list 640.3835 868.7967) 
(list 640.3913 868.8069) 
(list 640.3997 868.8172) 
(list 640.4085 868.8275) 
(list 640.4173 868.8378) 
(list 640.426 868.8481) 
(list 640.4342 868.8583) 
(list 640.4417 868.8686) 
(list 640.4482 868.8789) 
(list 640.4536 868.8892) 
(list 640.4577 868.8994) 
(list 640.4603 868.9097) 
(list 640.4614 868.92) 
(list 640.4614 868.92)))
(apply 'command (append '("pline") coords '("c")))
(setq tap2 (ssadd (entlast) tap2))
(command "_mirror" (entlast) "" "640,900" "640,901" "No")
(setq tap2 (ssadd (entlast) tap2))
(setq coords (list 
(list 641.092 868.55) 
(list 640.4614 868.55) 
(list 640.4614 868.5603) 
(list 640.4614 868.5706) 
(list 640.4614 868.5808) 
(list 640.4614 868.5911) 
(list 640.4614 868.6014) 
(list 640.4614 868.6117) 
(list 640.4614 868.6219) 
(list 640.4614 868.6322) 
(list 640.4614 868.6425) 
(list 640.4614 868.6528) 
(list 640.4614 868.6631) 
(list 640.4614 868.6733) 
(list 640.4614 868.6836) 
(list 640.4614 868.6939) 
(list 640.4614 868.7042) 
(list 640.4614 868.7144) 
(list 640.4614 868.7247) 
(list 640.4614 868.735) 
(list 640.4614 868.7453) 
(list 640.4614 868.7556) 
(list 640.4614 868.7658) 
(list 640.4614 868.7761) 
(list 640.4614 868.7864) 
(list 640.4614 868.7967) 
(list 640.4614 868.8069) 
(list 640.4614 868.8172) 
(list 640.4614 868.8275) 
(list 640.4614 868.8378) 
(list 640.4614 868.8481) 
(list 640.4614 868.8583) 
(list 640.4614 868.8686) 
(list 640.4614 868.8789) 
(list 640.4614 868.8892) 
(list 640.4614 868.8994) 
(list 640.4614 868.9097) 
(list 640.4614 868.92) 
(list 641.092 868.92)))
(apply 'command (append '("pline") coords '("c")))
(setq tap2 (ssadd (entlast) tap2))
(command "_mirror" (entlast) "" "640,900" "640,901" "No")
(setq tap2 (ssadd (entlast) tap2))
(setq coords (list 
(list 640 868.92) 
(list 640.125 868.92) 
(list 640.125 868.9303) 
(list 640.125 868.9406) 
(list 640.125 868.9508) 
(list 640.125 868.9611) 
(list 640.125 868.9714) 
(list 640.125 868.9817) 
(list 640.125 868.9919) 
(list 640.125 869.0022) 
(list 640.125 869.0125) 
(list 640.125 869.0228) 
(list 640.125 869.0331) 
(list 640.125 869.0433) 
(list 640.125 869.0536) 
(list 640.125 869.0639) 
(list 640.125 869.0742) 
(list 640.125 869.0844) 
(list 640.125 869.0947) 
(list 640.125 869.105) 
(list 640.125 869.1153) 
(list 640.125 869.1256) 
(list 640.125 869.1358) 
(list 640.125 869.1461) 
(list 640.125 869.1564) 
(list 640.125 869.1667) 
(list 640.125 869.1769) 
(list 640.125 869.1872) 
(list 640.125 869.1975) 
(list 640.125 869.2078) 
(list 640.125 869.2181) 
(list 640.125 869.2283) 
(list 640.125 869.2386) 
(list 640.125 869.2489) 
(list 640.125 869.2592) 
(list 640.125 869.2694) 
(list 640.125 869.2797) 
(list 640.125 869.29) 
(list 640 869.29)))
(apply 'command (append '("pline") coords '("c")))
(setq tap2 (ssadd (entlast) tap2))
(command "_mirror" (entlast) "" "640,900" "640,901" "No")
(setq tap2 (ssadd (entlast) tap2))
(setq coords (list 
(list 640.4708 868.92) 
(list 640.4614 868.92) 
(list 640.4609 868.9303) 
(list 640.4587 868.9406) 
(list 640.455 868.9508) 
(list 640.4499 868.9611) 
(list 640.4434 868.9714) 
(list 640.4358 868.9817) 
(list 640.4274 868.9919) 
(list 640.4182 869.0022) 
(list 640.4088 869.0125) 
(list 640.3992 869.0228) 
(list 640.3898 869.0331) 
(list 640.3809 869.0433) 
(list 640.3728 869.0536) 
(list 640.3658 869.0639) 
(list 640.3599 869.0742) 
(list 640.3556 869.0844) 
(list 640.3528 869.0947) 
(list 640.3517 869.105) 
(list 640.3523 869.1153) 
(list 640.3547 869.1256) 
(list 640.3588 869.1358) 
(list 640.3644 869.1461) 
(list 640.3714 869.1564) 
(list 640.3797 869.1667) 
(list 640.3889 869.1769) 
(list 640.3988 869.1872) 
(list 640.409 869.1975) 
(list 640.4194 869.2078) 
(list 640.4296 869.2181) 
(list 640.4392 869.2283) 
(list 640.4479 869.2386) 
(list 640.4556 869.2489) 
(list 640.4619 869.2592) 
(list 640.4666 869.2694) 
(list 640.4696 869.2797) 
(list 640.4708 869.29) 
(list 640.4708 869.29)))
(apply 'command (append '("pline") coords '("c")))
(setq tap2 (ssadd (entlast) tap2))
(command "_mirror" (entlast) "" "640,900" "640,901" "No")
(setq tap2 (ssadd (entlast) tap2))
(setq coords (list 
(list 641.092 868.92) 
(list 640.4708 868.92) 
(list 640.4708 868.9303) 
(list 640.4708 868.9406) 
(list 640.4708 868.9508) 
(list 640.4708 868.9611) 
(list 640.4708 868.9714) 
(list 640.4708 868.9817) 
(list 640.4708 868.9919) 
(list 640.4708 869.0022) 
(list 640.4708 869.0125) 
(list 640.4708 869.0228) 
(list 640.4708 869.0331) 
(list 640.4708 869.0433) 
(list 640.4708 869.0536) 
(list 640.4708 869.0639) 
(list 640.4708 869.0742) 
(list 640.4708 869.0844) 
(list 640.4708 869.0947) 
(list 640.4708 869.105) 
(list 640.4708 869.1153) 
(list 640.4708 869.1256) 
(list 640.4708 869.1358) 
(list 640.4708 869.1461) 
(list 640.4708 869.1564) 
(list 640.4708 869.1667) 
(list 640.4708 869.1769) 
(list 640.4708 869.1872) 
(list 640.4708 869.1975) 
(list 640.4708 869.2078) 
(list 640.4708 869.2181) 
(list 640.4708 869.2283) 
(list 640.4708 869.2386) 
(list 640.4708 869.2489) 
(list 640.4708 869.2592) 
(list 640.4708 869.2694) 
(list 640.4708 869.2797) 
(list 640.4708 869.29) 
(list 641.092 869.29)))
(apply 'command (append '("pline") coords '("c")))
(setq tap2 (ssadd (entlast) tap2))
(command "_mirror" (entlast) "" "640,900" "640,901" "No")
(setq tap2 (ssadd (entlast) tap2))
(setq coords (list 
(list 640 869.29) 
(list 640.125 869.29) 
(list 640.125 869.3003) 
(list 640.125 869.3106) 
(list 640.125 869.3208) 
(list 640.125 869.3311) 
(list 640.125 869.3414) 
(list 640.125 869.3517) 
(list 640.125 869.3619) 
(list 640.125 869.3722) 
(list 640.125 869.3825) 
(list 640.125 869.3928) 
(list 640.125 869.4031) 
(list 640.125 869.4133) 
(list 640.125 869.4236) 
(list 640.125 869.4339) 
(list 640.125 869.4442) 
(list 640.125 869.4544) 
(list 640.125 869.4647) 
(list 640.125 869.475) 
(list 640.125 869.4853) 
(list 640.125 869.4956) 
(list 640.125 869.5058) 
(list 640.125 869.5161) 
(list 640.125 869.5264) 
(list 640.125 869.5367) 
(list 640.125 869.5469) 
(list 640.125 869.5572) 
(list 640.125 869.5675) 
(list 640.125 869.5778) 
(list 640.125 869.5881) 
(list 640.125 869.5983) 
(list 640.125 869.6086) 
(list 640.125 869.6189) 
(list 640.125 869.6292) 
(list 640.125 869.6394) 
(list 640.125 869.6497) 
(list 640.125 869.66) 
(list 640 869.66)))
(apply 'command (append '("pline") coords '("c")))
(setq tap2 (ssadd (entlast) tap2))
(command "_mirror" (entlast) "" "640,900" "640,901" "No")
(setq tap2 (ssadd (entlast) tap2))
(setq coords (list 
(list 640.4802 869.29) 
(list 640.4708 869.29) 
(list 640.4701 869.3003) 
(list 640.4676 869.3106) 
(list 640.4632 869.3208) 
(list 640.4572 869.3311) 
(list 640.4497 869.3414) 
(list 640.4408 869.3517) 
(list 640.431 869.3619) 
(list 640.4204 869.3722) 
(list 640.4094 869.3825) 
(list 640.3982 869.3928) 
(list 640.3874 869.4031) 
(list 640.3771 869.4133) 
(list 640.3678 869.4236) 
(list 640.3596 869.4339) 
(list 640.3529 869.4442) 
(list 640.3479 869.4544) 
(list 640.3447 869.4647) 
(list 640.3435 869.475) 
(list 640.3443 869.4853) 
(list 640.3471 869.4956) 
(list 640.3518 869.5058) 
(list 640.3583 869.5161) 
(list 640.3664 869.5264) 
(list 640.3759 869.5367) 
(list 640.3865 869.5469) 
(list 640.3978 869.5572) 
(list 640.4097 869.5675) 
(list 640.4216 869.5778) 
(list 640.4332 869.5881) 
(list 640.4442 869.5983) 
(list 640.4542 869.6086) 
(list 640.4629 869.6189) 
(list 640.4701 869.6292) 
(list 640.4755 869.6394) 
(list 640.4789 869.6497) 
(list 640.4802 869.66) 
(list 640.4802 869.66)))
(apply 'command (append '("pline") coords '("c")))
(setq tap2 (ssadd (entlast) tap2))
(command "_mirror" (entlast) "" "640,900" "640,901" "No")
(setq tap2 (ssadd (entlast) tap2))
(setq coords (list 
(list 641.092 869.29) 
(list 640.4802 869.29) 
(list 640.4802 869.3003) 
(list 640.4802 869.3106) 
(list 640.4802 869.3208) 
(list 640.4802 869.3311) 
(list 640.4802 869.3414) 
(list 640.4802 869.3517) 
(list 640.4802 869.3619) 
(list 640.4802 869.3722) 
(list 640.4802 869.3825) 
(list 640.4802 869.3928) 
(list 640.4802 869.4031) 
(list 640.4802 869.4133) 
(list 640.4802 869.4236) 
(list 640.4802 869.4339) 
(list 640.4802 869.4442) 
(list 640.4802 869.4544) 
(list 640.4802 869.4647) 
(list 640.4802 869.475) 
(list 640.4802 869.4853) 
(list 640.4802 869.4956) 
(list 640.4802 869.5058) 
(list 640.4802 869.5161) 
(list 640.4802 869.5264) 
(list 640.4802 869.5367) 
(list 640.4802 869.5469) 
(list 640.4802 869.5572) 
(list 640.4802 869.5675) 
(list 640.4802 869.5778) 
(list 640.4802 869.5881) 
(list 640.4802 869.5983) 
(list 640.4802 869.6086) 
(list 640.4802 869.6189) 
(list 640.4802 869.6292) 
(list 640.4802 869.6394) 
(list 640.4802 869.6497) 
(list 640.4802 869.66) 
(list 641.092 869.66)))
(apply 'command (append '("pline") coords '("c")))
(setq tap2 (ssadd (entlast) tap2))
(command "_mirror" (entlast) "" "640,900" "640,901" "No")
(setq tap2 (ssadd (entlast) tap2))
(setq coords (list 
(list 640 869.66) 
(list 640.125 869.66) 
(list 640.125 869.6703) 
(list 640.125 869.6806) 
(list 640.125 869.6908) 
(list 640.125 869.7011) 
(list 640.125 869.7114) 
(list 640.125 869.7217) 
(list 640.125 869.7319) 
(list 640.125 869.7422) 
(list 640.125 869.7525) 
(list 640.125 869.7628) 
(list 640.125 869.7731) 
(list 640.125 869.7833) 
(list 640.125 869.7936) 
(list 640.125 869.8039) 
(list 640.125 869.8142) 
(list 640.125 869.8244) 
(list 640.125 869.8347) 
(list 640.125 869.845) 
(list 640.125 869.8553) 
(list 640.125 869.8656) 
(list 640.125 869.8758) 
(list 640.125 869.8861) 
(list 640.125 869.8964) 
(list 640.125 869.9067) 
(list 640.125 869.9169) 
(list 640.125 869.9272) 
(list 640.125 869.9375) 
(list 640.125 869.9478) 
(list 640.125 869.9581) 
(list 640.125 869.9683) 
(list 640.125 869.9786) 
(list 640.125 869.9889) 
(list 640.125 869.9992) 
(list 640.125 870.0094) 
(list 640.125 870.0197) 
(list 640.125 870.03) 
(list 640 870.03)))
(apply 'command (append '("pline") coords '("c")))
(setq tap2 (ssadd (entlast) tap2))
(command "_mirror" (entlast) "" "640,900" "640,901" "No")
(setq tap2 (ssadd (entlast) tap2))
(setq coords (list 
(list 640.4896 869.66) 
(list 640.4802 869.66) 
(list 640.4794 869.6703) 
(list 640.4764 869.6806) 
(list 640.4715 869.6908) 
(list 640.4645 869.7011) 
(list 640.4559 869.7114) 
(list 640.4458 869.7217) 
(list 640.4346 869.7319) 
(list 640.4225 869.7422) 
(list 640.4099 869.7525) 
(list 640.3973 869.7628) 
(list 640.385 869.7731) 
(list 640.3733 869.7833) 
(list 640.3627 869.7936) 
(list 640.3535 869.8039) 
(list 640.3459 869.8142) 
(list 640.3402 869.8244) 
(list 640.3367 869.8347) 
(list 640.3353 869.845) 
(list 640.3362 869.8553) 
(list 640.3394 869.8656) 
(list 640.3447 869.8758) 
(list 640.3521 869.8861) 
(list 640.3613 869.8964) 
(list 640.3721 869.9067) 
(list 640.384 869.9169) 
(list 640.3969 869.9272) 
(list 640.4103 869.9375) 
(list 640.4237 869.9478) 
(list 640.4368 869.9581) 
(list 640.4492 869.9683) 
(list 640.4604 869.9786) 
(list 640.4703 869.9889) 
(list 640.4783 869.9992) 
(list 640.4843 870.0094) 
(list 640.4881 870.0197) 
(list 640.4896 870.03) 
(list 640.4896 870.03)))
(apply 'command (append '("pline") coords '("c")))
(setq tap2 (ssadd (entlast) tap2))
(command "_mirror" (entlast) "" "640,900" "640,901" "No")
(setq tap2 (ssadd (entlast) tap2))
(setq coords (list 
(list 641.092 869.66) 
(list 640.4896 869.66) 
(list 640.4896 869.6703) 
(list 640.4896 869.6806) 
(list 640.4896 869.6908) 
(list 640.4896 869.7011) 
(list 640.4896 869.7114) 
(list 640.4896 869.7217) 
(list 640.4896 869.7319) 
(list 640.4896 869.7422) 
(list 640.4896 869.7525) 
(list 640.4896 869.7628) 
(list 640.4896 869.7731) 
(list 640.4896 869.7833) 
(list 640.4896 869.7936) 
(list 640.4896 869.8039) 
(list 640.4896 869.8142) 
(list 640.4896 869.8244) 
(list 640.4896 869.8347) 
(list 640.4896 869.845) 
(list 640.4896 869.8553) 
(list 640.4896 869.8656) 
(list 640.4896 869.8758) 
(list 640.4896 869.8861) 
(list 640.4896 869.8964) 
(list 640.4896 869.9067) 
(list 640.4896 869.9169) 
(list 640.4896 869.9272) 
(list 640.4896 869.9375) 
(list 640.4896 869.9478) 
(list 640.4896 869.9581) 
(list 640.4896 869.9683) 
(list 640.4896 869.9786) 
(list 640.4896 869.9889) 
(list 640.4896 869.9992) 
(list 640.4896 870.0094) 
(list 640.4896 870.0197) 
(list 640.4896 870.03) 
(list 641.092 870.03)))
(apply 'command (append '("pline") coords '("c")))
(setq tap2 (ssadd (entlast) tap2))
(command "_mirror" (entlast) "" "640,900" "640,901" "No")
(setq tap2 (ssadd (entlast) tap2))
(setq coords (list 
(list 640 870.03) 
(list 640.125 870.03) 
(list 640.125 870.0403) 
(list 640.125 870.0506) 
(list 640.125 870.0608) 
(list 640.125 870.0711) 
(list 640.125 870.0814) 
(list 640.125 870.0917) 
(list 640.125 870.1019) 
(list 640.125 870.1122) 
(list 640.125 870.1225) 
(list 640.125 870.1328) 
(list 640.125 870.1431) 
(list 640.125 870.1533) 
(list 640.125 870.1636) 
(list 640.125 870.1739) 
(list 640.125 870.1842) 
(list 640.125 870.1944) 
(list 640.125 870.2047) 
(list 640.125 870.215) 
(list 640.125 870.2253) 
(list 640.125 870.2356) 
(list 640.125 870.2458) 
(list 640.125 870.2561) 
(list 640.125 870.2664) 
(list 640.125 870.2767) 
(list 640.125 870.2869) 
(list 640.125 870.2972) 
(list 640.125 870.3075) 
(list 640.125 870.3178) 
(list 640.125 870.3281) 
(list 640.125 870.3383) 
(list 640.125 870.3486) 
(list 640.125 870.3589) 
(list 640.125 870.3692) 
(list 640.125 870.3794) 
(list 640.125 870.3897) 
(list 640.125 870.4) 
(list 640 870.4)))
(apply 'command (append '("pline") coords '("c")))
(setq tap2 (ssadd (entlast) tap2))
(command "_mirror" (entlast) "" "640,900" "640,901" "No")
(setq tap2 (ssadd (entlast) tap2))
(setq coords (list 
(list 640.499 870.03) 
(list 640.4896 870.03) 
(list 640.4887 870.0403) 
(list 640.4853 870.0506) 
(list 640.4797 870.0608) 
(list 640.4719 870.0711) 
(list 640.4622 870.0814) 
(list 640.4508 870.0917) 
(list 640.4382 870.1019) 
(list 640.4246 870.1122) 
(list 640.4105 870.1225) 
(list 640.3964 870.1328) 
(list 640.3826 870.1431) 
(list 640.3695 870.1533) 
(list 640.3577 870.1636) 
(list 640.3473 870.1739) 
(list 640.3389 870.1842) 
(list 640.3326 870.1944) 
(list 640.3286 870.2047) 
(list 640.3271 870.215) 
(list 640.3281 870.2253) 
(list 640.3317 870.2356) 
(list 640.3377 870.2458) 
(list 640.346 870.2561) 
(list 640.3563 870.2664) 
(list 640.3683 870.2767) 
(list 640.3816 870.2869) 
(list 640.396 870.2972) 
(list 640.4108 870.3075) 
(list 640.4258 870.3178) 
(list 640.4404 870.3281) 
(list 640.4542 870.3383) 
(list 640.4667 870.3486) 
(list 640.4776 870.3589) 
(list 640.4865 870.3692) 
(list 640.4932 870.3794) 
(list 640.4974 870.3897) 
(list 640.499 870.4) 
(list 640.499 870.4)))
(apply 'command (append '("pline") coords '("c")))
(setq tap2 (ssadd (entlast) tap2))
(command "_mirror" (entlast) "" "640,900" "640,901" "No")
(setq tap2 (ssadd (entlast) tap2))
(setq coords (list 
(list 641.092 870.03) 
(list 640.499 870.03) 
(list 640.499 870.0403) 
(list 640.499 870.0506) 
(list 640.499 870.0608) 
(list 640.499 870.0711) 
(list 640.499 870.0814) 
(list 640.499 870.0917) 
(list 640.499 870.1019) 
(list 640.499 870.1122) 
(list 640.499 870.1225) 
(list 640.499 870.1328) 
(list 640.499 870.1431) 
(list 640.499 870.1533) 
(list 640.499 870.1636) 
(list 640.499 870.1739) 
(list 640.499 870.1842) 
(list 640.499 870.1944) 
(list 640.499 870.2047) 
(list 640.499 870.215) 
(list 640.499 870.2253) 
(list 640.499 870.2356) 
(list 640.499 870.2458) 
(list 640.499 870.2561) 
(list 640.499 870.2664) 
(list 640.499 870.2767) 
(list 640.499 870.2869) 
(list 640.499 870.2972) 
(list 640.499 870.3075) 
(list 640.499 870.3178) 
(list 640.499 870.3281) 
(list 640.499 870.3383) 
(list 640.499 870.3486) 
(list 640.499 870.3589) 
(list 640.499 870.3692) 
(list 640.499 870.3794) 
(list 640.499 870.3897) 
(list 640.499 870.4) 
(list 641.092 870.4)))
(apply 'command (append '("pline") coords '("c")))
(setq tap2 (ssadd (entlast) tap2))
(command "_mirror" (entlast) "" "640,900" "640,901" "No")
(setq tap2 (ssadd (entlast) tap2))
(setq coords (list 
(list 640 870.4) 
(list 640.125 870.4) 
(list 640.125 870.4103) 
(list 640.125 870.4206) 
(list 640.125 870.4308) 
(list 640.125 870.4411) 
(list 640.125 870.4514) 
(list 640.125 870.4617) 
(list 640.125 870.4719) 
(list 640.125 870.4822) 
(list 640.125 870.4925) 
(list 640.125 870.5028) 
(list 640.125 870.5131) 
(list 640.125 870.5233) 
(list 640.125 870.5336) 
(list 640.125 870.5439) 
(list 640.125 870.5542) 
(list 640.125 870.5644) 
(list 640.125 870.5747) 
(list 640.125 870.585) 
(list 640.125 870.5953) 
(list 640.125 870.6056) 
(list 640.125 870.6158) 
(list 640.125 870.6261) 
(list 640.125 870.6364) 
(list 640.125 870.6467) 
(list 640.125 870.6569) 
(list 640.125 870.6672) 
(list 640.125 870.6775) 
(list 640.125 870.6878) 
(list 640.125 870.6981) 
(list 640.125 870.7083) 
(list 640.125 870.7186) 
(list 640.125 870.7289) 
(list 640.125 870.7392) 
(list 640.125 870.7494) 
(list 640.125 870.7597) 
(list 640.125 870.77) 
(list 640 870.77)))
(apply 'command (append '("pline") coords '("c")))
(setq tap2 (ssadd (entlast) tap2))
(command "_mirror" (entlast) "" "640,900" "640,901" "No")
(setq tap2 (ssadd (entlast) tap2))
(setq coords (list 
(list 640.5084 870.4) 
(list 640.499 870.4) 
(list 640.4979 870.4103) 
(list 640.4942 870.4206) 
(list 640.4879 870.4308) 
(list 640.4792 870.4411) 
(list 640.4684 870.4514) 
(list 640.4558 870.4617) 
(list 640.4418 870.4719) 
(list 640.4268 870.4822) 
(list 640.4112 870.4925) 
(list 640.3955 870.5028) 
(list 640.3802 870.5131) 
(list 640.3657 870.5233) 
(list 640.3526 870.5336) 
(list 640.3412 870.5439) 
(list 640.3319 870.5542) 
(list 640.3249 870.5644) 
(list 640.3205 870.5747) 
(list 640.3189 870.585) 
(list 640.3201 870.5953) 
(list 640.324 870.6056) 
(list 640.3307 870.6158) 
(list 640.3398 870.6261) 
(list 640.3512 870.6364) 
(list 640.3645 870.6467) 
(list 640.3792 870.6569) 
(list 640.395 870.6672) 
(list 640.4114 870.6775) 
(list 640.4279 870.6878) 
(list 640.444 870.6981) 
(list 640.4592 870.7083) 
(list 640.473 870.7186) 
(list 640.4849 870.7289) 
(list 640.4947 870.7392) 
(list 640.5021 870.7494) 
(list 640.5067 870.7597) 
(list 640.5084 870.77) 
(list 640.5084 870.77)))
(apply 'command (append '("pline") coords '("c")))
(setq tap2 (ssadd (entlast) tap2))
(command "_mirror" (entlast) "" "640,900" "640,901" "No")
(setq tap2 (ssadd (entlast) tap2))
(setq coords (list 
(list 641.092 870.4) 
(list 640.5084 870.4) 
(list 640.5084 870.4103) 
(list 640.5084 870.4206) 
(list 640.5084 870.4308) 
(list 640.5084 870.4411) 
(list 640.5084 870.4514) 
(list 640.5084 870.4617) 
(list 640.5084 870.4719) 
(list 640.5084 870.4822) 
(list 640.5084 870.4925) 
(list 640.5084 870.5028) 
(list 640.5084 870.5131) 
(list 640.5084 870.5233) 
(list 640.5084 870.5336) 
(list 640.5084 870.5439) 
(list 640.5084 870.5542) 
(list 640.5084 870.5644) 
(list 640.5084 870.5747) 
(list 640.5084 870.585) 
(list 640.5084 870.5953) 
(list 640.5084 870.6056) 
(list 640.5084 870.6158) 
(list 640.5084 870.6261) 
(list 640.5084 870.6364) 
(list 640.5084 870.6467) 
(list 640.5084 870.6569) 
(list 640.5084 870.6672) 
(list 640.5084 870.6775) 
(list 640.5084 870.6878) 
(list 640.5084 870.6981) 
(list 640.5084 870.7083) 
(list 640.5084 870.7186) 
(list 640.5084 870.7289) 
(list 640.5084 870.7392) 
(list 640.5084 870.7494) 
(list 640.5084 870.7597) 
(list 640.5084 870.77) 
(list 641.092 870.77)))
(apply 'command (append '("pline") coords '("c")))
(setq tap2 (ssadd (entlast) tap2))
(command "_mirror" (entlast) "" "640,900" "640,901" "No")
(setq tap2 (ssadd (entlast) tap2))
(setq coords (list 
(list 640 870.77) 
(list 640.125 870.77) 
(list 640.125 870.7803) 
(list 640.125 870.7906) 
(list 640.125 870.8008) 
(list 640.125 870.8111) 
(list 640.125 870.8214) 
(list 640.125 870.8317) 
(list 640.125 870.8419) 
(list 640.125 870.8522) 
(list 640.125 870.8625) 
(list 640.125 870.8728) 
(list 640.125 870.8831) 
(list 640.125 870.8933) 
(list 640.125 870.9036) 
(list 640.125 870.9139) 
(list 640.125 870.9242) 
(list 640.125 870.9344) 
(list 640.125 870.9447) 
(list 640.125 870.955) 
(list 640.125 870.9653) 
(list 640.125 870.9756) 
(list 640.125 870.9858) 
(list 640.125 870.9961) 
(list 640.125 871.0064) 
(list 640.125 871.0167) 
(list 640.125 871.0269) 
(list 640.125 871.0372) 
(list 640.125 871.0475) 
(list 640.125 871.0578) 
(list 640.125 871.0681) 
(list 640.125 871.0783) 
(list 640.125 871.0886) 
(list 640.125 871.0989) 
(list 640.125 871.1092) 
(list 640.125 871.1194) 
(list 640.125 871.1297) 
(list 640.125 871.14) 
(list 640 871.14)))
(apply 'command (append '("pline") coords '("c")))
(setq tap2 (ssadd (entlast) tap2))
(command "_mirror" (entlast) "" "640,900" "640,901" "No")
(setq tap2 (ssadd (entlast) tap2))
(setq coords (list 
(list 640.5178 870.77) 
(list 640.5084 870.77) 
(list 640.5072 870.7803) 
(list 640.5031 870.7906) 
(list 640.4961 870.8008) 
(list 640.4866 870.8111) 
(list 640.4747 870.8214) 
(list 640.4608 870.8317) 
(list 640.4454 870.8419) 
(list 640.4289 870.8522) 
(list 640.4117 870.8625) 
(list 640.3945 870.8728) 
(list 640.3778 870.8831) 
(list 640.3619 870.8933) 
(list 640.3476 870.9036) 
(list 640.3351 870.9139) 
(list 640.3248 870.9242) 
(list 640.3172 870.9344) 
(list 640.3125 870.9447) 
(list 640.3107 870.955) 
(list 640.312 870.9653) 
(list 640.3164 870.9756) 
(list 640.3237 870.9858) 
(list 640.3337 870.9961) 
(list 640.3461 871.0064) 
(list 640.3607 871.0167) 
(list 640.3768 871.0269) 
(list 640.3941 871.0372) 
(list 640.4121 871.0475) 
(list 640.4301 871.0578) 
(list 640.4476 871.0681) 
(list 640.4642 871.0783) 
(list 640.4792 871.0886) 
(list 640.4923 871.0989) 
(list 640.503 871.1092) 
(list 640.5109 871.1194) 
(list 640.5159 871.1297) 
(list 640.5178 871.14) 
(list 640.5178 871.14)))
(apply 'command (append '("pline") coords '("c")))
(setq tap2 (ssadd (entlast) tap2))
(command "_mirror" (entlast) "" "640,900" "640,901" "No")
(setq tap2 (ssadd (entlast) tap2))
(setq coords (list 
(list 641.092 870.77) 
(list 640.5178 870.77) 
(list 640.5178 870.7803) 
(list 640.5178 870.7906) 
(list 640.5178 870.8008) 
(list 640.5178 870.8111) 
(list 640.5178 870.8214) 
(list 640.5178 870.8317) 
(list 640.5178 870.8419) 
(list 640.5178 870.8522) 
(list 640.5178 870.8625) 
(list 640.5178 870.8728) 
(list 640.5178 870.8831) 
(list 640.5178 870.8933) 
(list 640.5178 870.9036) 
(list 640.5178 870.9139) 
(list 640.5178 870.9242) 
(list 640.5178 870.9344) 
(list 640.5178 870.9447) 
(list 640.5178 870.955) 
(list 640.5178 870.9653) 
(list 640.5178 870.9756) 
(list 640.5178 870.9858) 
(list 640.5178 870.9961) 
(list 640.5178 871.0064) 
(list 640.5178 871.0167) 
(list 640.5178 871.0269) 
(list 640.5178 871.0372) 
(list 640.5178 871.0475) 
(list 640.5178 871.0578) 
(list 640.5178 871.0681) 
(list 640.5178 871.0783) 
(list 640.5178 871.0886) 
(list 640.5178 871.0989) 
(list 640.5178 871.1092) 
(list 640.5178 871.1194) 
(list 640.5178 871.1297) 
(list 640.5178 871.14) 
(list 641.092 871.14)))
(apply 'command (append '("pline") coords '("c")))
(setq tap2 (ssadd (entlast) tap2))
(command "_mirror" (entlast) "" "640,900" "640,901" "No")
(setq tap2 (ssadd (entlast) tap2))
(setq coords (list 
(list 640 871.14) 
(list 640.125 871.14) 
(list 640.125 871.1503) 
(list 640.125 871.1606) 
(list 640.125 871.1708) 
(list 640.125 871.1811) 
(list 640.125 871.1914) 
(list 640.125 871.2017) 
(list 640.125 871.2119) 
(list 640.125 871.2222) 
(list 640.125 871.2325) 
(list 640.125 871.2428) 
(list 640.125 871.2531) 
(list 640.125 871.2633) 
(list 640.125 871.2736) 
(list 640.125 871.2839) 
(list 640.125 871.2942) 
(list 640.125 871.3044) 
(list 640.125 871.3147) 
(list 640.125 871.325) 
(list 640.125 871.3353) 
(list 640.125 871.3456) 
(list 640.125 871.3558) 
(list 640.125 871.3661) 
(list 640.125 871.3764) 
(list 640.125 871.3867) 
(list 640.125 871.3969) 
(list 640.125 871.4072) 
(list 640.125 871.4175) 
(list 640.125 871.4278) 
(list 640.125 871.4381) 
(list 640.125 871.4483) 
(list 640.125 871.4586) 
(list 640.125 871.4689) 
(list 640.125 871.4792) 
(list 640.125 871.4894) 
(list 640.125 871.4997) 
(list 640.125 871.51) 
(list 640 871.51)))
(apply 'command (append '("pline") coords '("c")))
(setq tap2 (ssadd (entlast) tap2))
(command "_mirror" (entlast) "" "640,900" "640,901" "No")
(setq tap2 (ssadd (entlast) tap2))
(setq coords (list 
(list 640.5272 871.14) 
(list 640.5178 871.14) 
(list 640.5165 871.1503) 
(list 640.5119 871.1606) 
(list 640.5043 871.1708) 
(list 640.4939 871.1811) 
(list 640.4809 871.1914) 
(list 640.4658 871.2017) 
(list 640.449 871.2119) 
(list 640.431 871.2222) 
(list 640.4123 871.2325) 
(list 640.3936 871.2428) 
(list 640.3753 871.2531) 
(list 640.3581 871.2633) 
(list 640.3425 871.2736) 
(list 640.3289 871.2839) 
(list 640.3178 871.2942) 
(list 640.3096 871.3044) 
(list 640.3044 871.3147) 
(list 640.3025 871.325) 
(list 640.3039 871.3353) 
(list 640.3087 871.3456) 
(list 640.3167 871.3558) 
(list 640.3276 871.3661) 
(list 640.3411 871.3764) 
(list 640.3569 871.3867) 
(list 640.3744 871.3969) 
(list 640.3932 871.4072) 
(list 640.4126 871.4175) 
(list 640.4322 871.4278) 
(list 640.4512 871.4381) 
(list 640.4692 871.4483) 
(list 640.4855 871.4586) 
(list 640.4996 871.4689) 
(list 640.5112 871.4792) 
(list 640.5198 871.4894) 
(list 640.5252 871.4997) 
(list 640.5272 871.51) 
(list 640.5272 871.51)))
(apply 'command (append '("pline") coords '("c")))
(setq tap2 (ssadd (entlast) tap2))
(command "_mirror" (entlast) "" "640,900" "640,901" "No")
(setq tap2 (ssadd (entlast) tap2))
(setq coords (list 
(list 641.092 871.14) 
(list 640.5272 871.14) 
(list 640.5272 871.1503) 
(list 640.5272 871.1606) 
(list 640.5272 871.1708) 
(list 640.5272 871.1811) 
(list 640.5272 871.1914) 
(list 640.5272 871.2017) 
(list 640.5272 871.2119) 
(list 640.5272 871.2222) 
(list 640.5272 871.2325) 
(list 640.5272 871.2428) 
(list 640.5272 871.2531) 
(list 640.5272 871.2633) 
(list 640.5272 871.2736) 
(list 640.5272 871.2839) 
(list 640.5272 871.2942) 
(list 640.5272 871.3044) 
(list 640.5272 871.3147) 
(list 640.5272 871.325) 
(list 640.5272 871.3353) 
(list 640.5272 871.3456) 
(list 640.5272 871.3558) 
(list 640.5272 871.3661) 
(list 640.5272 871.3764) 
(list 640.5272 871.3867) 
(list 640.5272 871.3969) 
(list 640.5272 871.4072) 
(list 640.5272 871.4175) 
(list 640.5272 871.4278) 
(list 640.5272 871.4381) 
(list 640.5272 871.4483) 
(list 640.5272 871.4586) 
(list 640.5272 871.4689) 
(list 640.5272 871.4792) 
(list 640.5272 871.4894) 
(list 640.5272 871.4997) 
(list 640.5272 871.51) 
(list 641.092 871.51)))
(apply 'command (append '("pline") coords '("c")))
(setq tap2 (ssadd (entlast) tap2))
(command "_mirror" (entlast) "" "640,900" "640,901" "No")
(setq tap2 (ssadd (entlast) tap2))
(setq coords (list 
(list 640 871.51) 
(list 640.125 871.51) 
(list 640.125 871.5203) 
(list 640.125 871.5306) 
(list 640.125 871.5408) 
(list 640.125 871.5511) 
(list 640.125 871.5614) 
(list 640.125 871.5717) 
(list 640.125 871.5819) 
(list 640.125 871.5922) 
(list 640.125 871.6025) 
(list 640.125 871.6128) 
(list 640.125 871.6231) 
(list 640.125 871.6333) 
(list 640.125 871.6436) 
(list 640.125 871.6539) 
(list 640.125 871.6642) 
(list 640.125 871.6744) 
(list 640.125 871.6847) 
(list 640.125 871.695) 
(list 640.125 871.7053) 
(list 640.125 871.7156) 
(list 640.125 871.7258) 
(list 640.125 871.7361) 
(list 640.125 871.7464) 
(list 640.125 871.7567) 
(list 640.125 871.7669) 
(list 640.125 871.7772) 
(list 640.125 871.7875) 
(list 640.125 871.7978) 
(list 640.125 871.8081) 
(list 640.125 871.8183) 
(list 640.125 871.8286) 
(list 640.125 871.8389) 
(list 640.125 871.8492) 
(list 640.125 871.8594) 
(list 640.125 871.8697) 
(list 640.125 871.88) 
(list 640 871.88)))
(apply 'command (append '("pline") coords '("c")))
(setq tap2 (ssadd (entlast) tap2))
(command "_mirror" (entlast) "" "640,900" "640,901" "No")
(setq tap2 (ssadd (entlast) tap2))
(setq coords (list 
(list 640.5366 871.51) 
(list 640.5272 871.51) 
(list 640.5257 871.5203) 
(list 640.5208 871.5306) 
(list 640.5126 871.5408) 
(list 640.5013 871.5511) 
(list 640.4872 871.5614) 
(list 640.4708 871.5717) 
(list 640.4526 871.5819) 
(list 640.4331 871.5922) 
(list 640.413 871.6025) 
(list 640.3927 871.6128) 
(list 640.3729 871.6231) 
(list 640.3543 871.6333) 
(list 640.3374 871.6436) 
(list 640.3228 871.6539) 
(list 640.3108 871.6642) 
(list 640.3019 871.6744) 
(list 640.2963 871.6847) 
(list 640.2943 871.695) 
(list 640.2959 871.7053) 
(list 640.301 871.7156) 
(list 640.3096 871.7258) 
(list 640.3214 871.7361) 
(list 640.336 871.7464) 
(list 640.3531 871.7567) 
(list 640.372 871.7669) 
(list 640.3923 871.7772) 
(list 640.4132 871.7875) 
(list 640.4343 871.7978) 
(list 640.4548 871.8081) 
(list 640.4742 871.8183) 
(list 640.4917 871.8286) 
(list 640.507 871.8389) 
(list 640.5194 871.8492) 
(list 640.5287 871.8594) 
(list 640.5345 871.8697) 
(list 640.5366 871.88) 
(list 640.5366 871.88)))
(apply 'command (append '("pline") coords '("c")))
(setq tap2 (ssadd (entlast) tap2))
(command "_mirror" (entlast) "" "640,900" "640,901" "No")
(setq tap2 (ssadd (entlast) tap2))
(setq coords (list 
(list 641.092 871.51) 
(list 640.5366 871.51) 
(list 640.5366 871.5203) 
(list 640.5366 871.5306) 
(list 640.5366 871.5408) 
(list 640.5366 871.5511) 
(list 640.5366 871.5614) 
(list 640.5366 871.5717) 
(list 640.5366 871.5819) 
(list 640.5366 871.5922) 
(list 640.5366 871.6025) 
(list 640.5366 871.6128) 
(list 640.5366 871.6231) 
(list 640.5366 871.6333) 
(list 640.5366 871.6436) 
(list 640.5366 871.6539) 
(list 640.5366 871.6642) 
(list 640.5366 871.6744) 
(list 640.5366 871.6847) 
(list 640.5366 871.695) 
(list 640.5366 871.7053) 
(list 640.5366 871.7156) 
(list 640.5366 871.7258) 
(list 640.5366 871.7361) 
(list 640.5366 871.7464) 
(list 640.5366 871.7567) 
(list 640.5366 871.7669) 
(list 640.5366 871.7772) 
(list 640.5366 871.7875) 
(list 640.5366 871.7978) 
(list 640.5366 871.8081) 
(list 640.5366 871.8183) 
(list 640.5366 871.8286) 
(list 640.5366 871.8389) 
(list 640.5366 871.8492) 
(list 640.5366 871.8594) 
(list 640.5366 871.8697) 
(list 640.5366 871.88) 
(list 641.092 871.88)))
(apply 'command (append '("pline") coords '("c")))
(setq tap2 (ssadd (entlast) tap2))
(command "_mirror" (entlast) "" "640,900" "640,901" "No")
(setq tap2 (ssadd (entlast) tap2))
(setq coords (list 
(list 640 871.88) 
(list 640.125 871.88) 
(list 640.125 871.8903) 
(list 640.125 871.9006) 
(list 640.125 871.9108) 
(list 640.125 871.9211) 
(list 640.125 871.9314) 
(list 640.125 871.9417) 
(list 640.125 871.9519) 
(list 640.125 871.9622) 
(list 640.125 871.9725) 
(list 640.125 871.9828) 
(list 640.125 871.9931) 
(list 640.125 872.0033) 
(list 640.125 872.0136) 
(list 640.125 872.0239) 
(list 640.125 872.0342) 
(list 640.125 872.0444) 
(list 640.125 872.0547) 
(list 640.125 872.065) 
(list 640.125 872.0753) 
(list 640.125 872.0856) 
(list 640.125 872.0958) 
(list 640.125 872.1061) 
(list 640.125 872.1164) 
(list 640.125 872.1267) 
(list 640.125 872.1369) 
(list 640.125 872.1472) 
(list 640.125 872.1575) 
(list 640.125 872.1678) 
(list 640.125 872.1781) 
(list 640.125 872.1883) 
(list 640.125 872.1986) 
(list 640.125 872.2089) 
(list 640.125 872.2192) 
(list 640.125 872.2294) 
(list 640.125 872.2397) 
(list 640.125 872.25) 
(list 640 872.25)))
(apply 'command (append '("pline") coords '("c")))
(setq tap2 (ssadd (entlast) tap2))
(command "_mirror" (entlast) "" "640,900" "640,901" "No")
(setq tap2 (ssadd (entlast) tap2))
(setq coords (list 
(list 640.546 871.88) 
(list 640.5366 871.88) 
(list 640.535 871.8903) 
(list 640.5297 871.9006) 
(list 640.5208 871.9108) 
(list 640.5086 871.9211) 
(list 640.4935 871.9314) 
(list 640.4758 871.9417) 
(list 640.4562 871.9519) 
(list 640.4353 871.9622) 
(list 640.4135 871.9725) 
(list 640.3917 871.9828) 
(list 640.3705 871.9931) 
(list 640.3505 872.0033) 
(list 640.3324 872.0136) 
(list 640.3166 872.0239) 
(list 640.3038 872.0342) 
(list 640.2942 872.0444) 
(list 640.2883 872.0547) 
(list 640.2861 872.065) 
(list 640.2878 872.0753) 
(list 640.2934 872.0856) 
(list 640.3026 872.0958) 
(list 640.3153 872.1061) 
(list 640.331 872.1164) 
(list 640.3493 872.1267) 
(list 640.3696 872.1369) 
(list 640.3913 872.1472) 
(list 640.4139 872.1575) 
(list 640.4364 872.1678) 
(list 640.4584 872.1781) 
(list 640.4792 872.1883) 
(list 640.498 872.1986) 
(list 640.5143 872.2089) 
(list 640.5276 872.2192) 
(list 640.5375 872.2294) 
(list 640.5437 872.2397) 
(list 640.546 872.25) 
(list 640.546 872.25)))
(apply 'command (append '("pline") coords '("c")))
(setq tap2 (ssadd (entlast) tap2))
(command "_mirror" (entlast) "" "640,900" "640,901" "No")
(setq tap2 (ssadd (entlast) tap2))
(setq coords (list 
(list 641.092 871.88) 
(list 640.546 871.88) 
(list 640.546 871.8903) 
(list 640.546 871.9006) 
(list 640.546 871.9108) 
(list 640.546 871.9211) 
(list 640.546 871.9314) 
(list 640.546 871.9417) 
(list 640.546 871.9519) 
(list 640.546 871.9622) 
(list 640.546 871.9725) 
(list 640.546 871.9828) 
(list 640.546 871.9931) 
(list 640.546 872.0033) 
(list 640.546 872.0136) 
(list 640.546 872.0239) 
(list 640.546 872.0342) 
(list 640.546 872.0444) 
(list 640.546 872.0547) 
(list 640.546 872.065) 
(list 640.546 872.0753) 
(list 640.546 872.0856) 
(list 640.546 872.0958) 
(list 640.546 872.1061) 
(list 640.546 872.1164) 
(list 640.546 872.1267) 
(list 640.546 872.1369) 
(list 640.546 872.1472) 
(list 640.546 872.1575) 
(list 640.546 872.1678) 
(list 640.546 872.1781) 
(list 640.546 872.1883) 
(list 640.546 872.1986) 
(list 640.546 872.2089) 
(list 640.546 872.2192) 
(list 640.546 872.2294) 
(list 640.546 872.2397) 
(list 640.546 872.25) 
(list 641.092 872.25)))
(apply 'command (append '("pline") coords '("c")))
(setq tap2 (ssadd (entlast) tap2))
(command "_mirror" (entlast) "" "640,900" "640,901" "No")
(setq tap2 (ssadd (entlast) tap2))
(command "_block" "blktap2" "640,900" tap2 "")
(command "_insert" "blktap2" "640,900" "1" "1" "0")
(command "_insert" "blktap2" "640,900" "1" "1" "180")
(setq uc2 nil)
(setq uc2 (ssadd))
(setq coords (list 
(list 0 -0.185) 
(list 0.125 -0.185) 
(list 0.125 -0.17472) 
(list 0.125 -0.16444) 
(list 0.125 -0.15417) 
(list 0.125 -0.14389) 
(list 0.125 -0.13361) 
(list 0.125 -0.12333) 
(list 0.125 -0.11306) 
(list 0.125 -0.10278) 
(list 0.125 -0.0925) 
(list 0.125 -0.082222) 
(list 0.125 -0.071944) 
(list 0.125 -0.061667) 
(list 0.125 -0.051389) 
(list 0.125 -0.041111) 
(list 0.125 -0.030833) 
(list 0.125 -0.020556) 
(list 0.125 -0.010278) 
(list 0.125 0) 
(list 0.125 0.010278) 
(list 0.125 0.020556) 
(list 0.125 0.030833) 
(list 0.125 0.041111) 
(list 0.125 0.051389) 
(list 0.125 0.061667) 
(list 0.125 0.071944) 
(list 0.125 0.082222) 
(list 0.125 0.0925) 
(list 0.125 0.10278) 
(list 0.125 0.11306) 
(list 0.125 0.12333) 
(list 0.125 0.13361) 
(list 0.125 0.14389) 
(list 0.125 0.15417) 
(list 0.125 0.16444) 
(list 0.125 0.17472) 
(list 0.125 0.185) 
(list 0 0.185)))
(apply 'command (append '("pline") coords '("c")))
(setq uc2 (ssadd (entlast) uc2))
(setq coords (list 
(list 1.092 -0.185) 
(list 0.546 -0.185) 
(list 0.544 -0.17472) 
(list 0.53804 -0.16444) 
(list 0.52831 -0.15417) 
(list 0.51512 -0.14389) 
(list 0.49885 -0.13361) 
(list 0.48 -0.12333) 
(list 0.45915 -0.11306) 
(list 0.43692 -0.10278) 
(list 0.414 -0.0925) 
(list 0.39108 -0.082222) 
(list 0.36885 -0.071944) 
(list 0.348 -0.061667) 
(list 0.32915 -0.051389) 
(list 0.31288 -0.041111) 
(list 0.29968 -0.030833) 
(list 0.28996 -0.020556) 
(list 0.28401 -0.010278) 
(list 0.282 0) 
(list 0.28401 0.010278) 
(list 0.28996 0.020556) 
(list 0.29968 0.030833) 
(list 0.31288 0.041111) 
(list 0.32915 0.051389) 
(list 0.348 0.061667) 
(list 0.36885 0.071944) 
(list 0.39108 0.082222) 
(list 0.414 0.0925) 
(list 0.43692 0.10278) 
(list 0.45915 0.11306) 
(list 0.48 0.12333) 
(list 0.49885 0.13361) 
(list 0.51512 0.14389) 
(list 0.52831 0.15417) 
(list 0.53804 0.16444) 
(list 0.544 0.17472) 
(list 0.546 0.185) 
(list 1.092 0.185)))
(apply 'command (append '("pline") coords '("c")))
(setq uc2 (ssadd (entlast) uc2))
(command "_block" "blkuc2" "0,0.185" uc2 "")
(command "_insert" "blkuc2" "640,872.62" "1" "1" "0")
(command "_insert" "blkuc2" "640,872.25" "1" "1" "180")
(command "_insert" "blkuc2" "640,872.99" "1" "1" "0")
(command "_insert" "blkuc2" "640,872.62" "1" "1" "180")
(command "_insert" "blkuc2" "640,873.36" "1" "1" "0")
(command "_insert" "blkuc2" "640,872.99" "1" "1" "180")
(command "_insert" "blkuc2" "640,873.73" "1" "1" "0")
(command "_insert" "blkuc2" "640,873.36" "1" "1" "180")
(command "_insert" "blkuc2" "640,874.1" "1" "1" "0")
(command "_insert" "blkuc2" "640,873.73" "1" "1" "180")
(command "_insert" "blkuc2" "640,874.47" "1" "1" "0")
(command "_insert" "blkuc2" "640,874.1" "1" "1" "180")
(command "_insert" "blkuc2" "640,874.84" "1" "1" "0")
(command "_insert" "blkuc2" "640,874.47" "1" "1" "180")
(command "_insert" "blkuc2" "640,875.21" "1" "1" "0")
(command "_insert" "blkuc2" "640,874.84" "1" "1" "180")
(command "_insert" "blkuc2" "640,875.58" "1" "1" "0")
(command "_insert" "blkuc2" "640,875.21" "1" "1" "180")
(command "_insert" "blkuc2" "640,875.95" "1" "1" "0")
(command "_insert" "blkuc2" "640,875.58" "1" "1" "180")
(command "_insert" "blkuc2" "640,876.32" "1" "1" "0")
(command "_insert" "blkuc2" "640,875.95" "1" "1" "180")
(command "_insert" "blkuc2" "640,876.69" "1" "1" "0")
(command "_insert" "blkuc2" "640,876.32" "1" "1" "180")
(command "_insert" "blkuc2" "640,877.06" "1" "1" "0")
(command "_insert" "blkuc2" "640,876.69" "1" "1" "180")
(command "_insert" "blkuc2" "640,877.43" "1" "1" "0")
(command "_insert" "blkuc2" "640,877.06" "1" "1" "180")
(command "_insert" "blkuc2" "640,877.8" "1" "1" "0")
(command "_insert" "blkuc2" "640,877.43" "1" "1" "180")
(command "_insert" "blkuc2" "640,878.17" "1" "1" "0")
(command "_insert" "blkuc2" "640,877.8" "1" "1" "180")
(command "_insert" "blkuc2" "640,878.54" "1" "1" "0")
(command "_insert" "blkuc2" "640,878.17" "1" "1" "180")
(command "_insert" "blkuc2" "640,878.91" "1" "1" "0")
(command "_insert" "blkuc2" "640,878.54" "1" "1" "180")
(command "_insert" "blkuc2" "640,879.28" "1" "1" "0")
(command "_insert" "blkuc2" "640,878.91" "1" "1" "180")
(command "_insert" "blkuc2" "640,879.65" "1" "1" "0")
(command "_insert" "blkuc2" "640,879.28" "1" "1" "180")
(command "_insert" "blkuc2" "640,880.02" "1" "1" "0")
(command "_insert" "blkuc2" "640,879.65" "1" "1" "180")
(command "_insert" "blkuc2" "640,880.39" "1" "1" "0")
(command "_insert" "blkuc2" "640,880.02" "1" "1" "180")
(command "_insert" "blkuc2" "640,880.76" "1" "1" "0")
(command "_insert" "blkuc2" "640,880.39" "1" "1" "180")
(command "_insert" "blkuc2" "640,881.13" "1" "1" "0")
(command "_insert" "blkuc2" "640,880.76" "1" "1" "180")
(command "_insert" "blkuc2" "640,881.5" "1" "1" "0")
(command "_insert" "blkuc2" "640,881.13" "1" "1" "180")
(command "_insert" "blkuc2" "640,881.87" "1" "1" "0")
(command "_insert" "blkuc2" "640,881.5" "1" "1" "180")
(command "_insert" "blkuc2" "640,882.24" "1" "1" "0")
(command "_insert" "blkuc2" "640,881.87" "1" "1" "180")
(command "_insert" "blkuc2" "640,882.61" "1" "1" "0")
(command "_insert" "blkuc2" "640,882.24" "1" "1" "180")
(command "_insert" "blkuc2" "640,882.98" "1" "1" "0")
(command "_insert" "blkuc2" "640,882.61" "1" "1" "180")
(command "_insert" "blkuc2" "640,883.35" "1" "1" "0")
(command "_insert" "blkuc2" "640,882.98" "1" "1" "180")
(command "_insert" "blkuc2" "640,883.72" "1" "1" "0")
(command "_insert" "blkuc2" "640,883.35" "1" "1" "180")
(command "_insert" "blkuc2" "640,884.09" "1" "1" "0")
(command "_insert" "blkuc2" "640,883.72" "1" "1" "180")
(command "_insert" "blkuc2" "640,884.46" "1" "1" "0")
(command "_insert" "blkuc2" "640,884.09" "1" "1" "180")
(command "_insert" "blkuc2" "640,884.83" "1" "1" "0")
(command "_insert" "blkuc2" "640,884.46" "1" "1" "180")
(command "_insert" "blkuc2" "640,885.2" "1" "1" "0")
(command "_insert" "blkuc2" "640,884.83" "1" "1" "180")
(command "_insert" "blkuc2" "640,885.57" "1" "1" "0")
(command "_insert" "blkuc2" "640,885.2" "1" "1" "180")
(command "_insert" "blkuc2" "640,885.94" "1" "1" "0")
(command "_insert" "blkuc2" "640,885.57" "1" "1" "180")
(command "_insert" "blkuc2" "640,886.31" "1" "1" "0")
(command "_insert" "blkuc2" "640,885.94" "1" "1" "180")
(command "_insert" "blkuc2" "640,886.68" "1" "1" "0")
(command "_insert" "blkuc2" "640,886.31" "1" "1" "180")
(command "_insert" "blkuc2" "640,887.05" "1" "1" "0")
(command "_insert" "blkuc2" "640,886.68" "1" "1" "180")
(command "_insert" "blkuc2" "640,887.42" "1" "1" "0")
(command "_insert" "blkuc2" "640,887.05" "1" "1" "180")
(command "_insert" "blkuc2" "640,887.79" "1" "1" "0")
(command "_insert" "blkuc2" "640,887.42" "1" "1" "180")
(command "_insert" "blkuc2" "640,888.16" "1" "1" "0")
(command "_insert" "blkuc2" "640,887.79" "1" "1" "180")
(command "_insert" "blkuc2" "640,888.53" "1" "1" "0")
(command "_insert" "blkuc2" "640,888.16" "1" "1" "180")
(command "_insert" "blkuc2" "640,888.9" "1" "1" "0")
(command "_insert" "blkuc2" "640,888.53" "1" "1" "180")
(command "_insert" "blkuc2" "640,889.27" "1" "1" "0")
(command "_insert" "blkuc2" "640,888.9" "1" "1" "180")
(command "_insert" "blkuc2" "640,889.64" "1" "1" "0")
(command "_insert" "blkuc2" "640,889.27" "1" "1" "180")
(command "_insert" "blkuc2" "640,890.01" "1" "1" "0")
(command "_insert" "blkuc2" "640,889.64" "1" "1" "180")
(command "_insert" "blkuc2" "640,890.38" "1" "1" "0")
(command "_insert" "blkuc2" "640,890.01" "1" "1" "180")
(command "_insert" "blkuc2" "640,890.75" "1" "1" "0")
(command "_insert" "blkuc2" "640,890.38" "1" "1" "180")
(command "_insert" "blkuc2" "640,891.12" "1" "1" "0")
(command "_insert" "blkuc2" "640,890.75" "1" "1" "180")
(command "_insert" "blkuc2" "640,891.49" "1" "1" "0")
(command "_insert" "blkuc2" "640,891.12" "1" "1" "180")
(command "_insert" "blkuc2" "640,891.86" "1" "1" "0")
(command "_insert" "blkuc2" "640,891.49" "1" "1" "180")
(command "_insert" "blkuc2" "640,892.23" "1" "1" "0")
(command "_insert" "blkuc2" "640,891.86" "1" "1" "180")
(command "_insert" "blkuc2" "640,892.6" "1" "1" "0")
(command "_insert" "blkuc2" "640,892.23" "1" "1" "180")
(command "_insert" "blkuc2" "640,892.97" "1" "1" "0")
(command "_insert" "blkuc2" "640,892.6" "1" "1" "180")
(command "_insert" "blkuc2" "640,893.34" "1" "1" "0")
(command "_insert" "blkuc2" "640,892.97" "1" "1" "180")
(command "_insert" "blkuc2" "640,893.71" "1" "1" "0")
(command "_insert" "blkuc2" "640,893.34" "1" "1" "180")
(command "_insert" "blkuc2" "640,894.08" "1" "1" "0")
(command "_insert" "blkuc2" "640,893.71" "1" "1" "180")
(command "_insert" "blkuc2" "640,894.45" "1" "1" "0")
(command "_insert" "blkuc2" "640,894.08" "1" "1" "180")
(command "_insert" "blkuc2" "640,894.82" "1" "1" "0")
(command "_insert" "blkuc2" "640,894.45" "1" "1" "180")
(command "_insert" "blkuc2" "640,895.19" "1" "1" "0")
(command "_insert" "blkuc2" "640,894.82" "1" "1" "180")
(command "_insert" "blkuc2" "640,895.56" "1" "1" "0")
(command "_insert" "blkuc2" "640,895.19" "1" "1" "180")
(command "_insert" "blkuc2" "640,895.93" "1" "1" "0")
(command "_insert" "blkuc2" "640,895.56" "1" "1" "180")
(command "_insert" "blkuc2" "640,896.3" "1" "1" "0")
(command "_insert" "blkuc2" "640,895.93" "1" "1" "180")
(command "_insert" "blkuc2" "640,896.67" "1" "1" "0")
(command "_insert" "blkuc2" "640,896.3" "1" "1" "180")
(command "_insert" "blkuc2" "640,897.04" "1" "1" "0")
(command "_insert" "blkuc2" "640,896.67" "1" "1" "180")
(command "_insert" "blkuc2" "640,897.41" "1" "1" "0")
(command "_insert" "blkuc2" "640,897.04" "1" "1" "180")
(command "_insert" "blkuc2" "640,897.78" "1" "1" "0")
(command "_insert" "blkuc2" "640,897.41" "1" "1" "180")
(command "_insert" "blkuc2" "640,898.15" "1" "1" "0")
(command "_insert" "blkuc2" "640,897.78" "1" "1" "180")
(command "_insert" "blkuc2" "640,898.52" "1" "1" "0")
(command "_insert" "blkuc2" "640,898.15" "1" "1" "180")
(command "_insert" "blkuc2" "640,898.89" "1" "1" "0")
(command "_insert" "blkuc2" "640,898.52" "1" "1" "180")
(command "_insert" "blkuc2" "640,899.26" "1" "1" "0")
(command "_insert" "blkuc2" "640,898.89" "1" "1" "180")
(command "_insert" "blkuc2" "640,899.63" "1" "1" "0")
(command "_insert" "blkuc2" "640,899.26" "1" "1" "180")
(command "_insert" "blkuc2" "640,900" "1" "1" "0")
(command "_insert" "blkuc2" "640,899.63" "1" "1" "180")
(command "_insert" "blkuc2" "640,900.37" "1" "1" "0")
(command "_insert" "blkuc2" "640,900" "1" "1" "180")
(command "_insert" "blkuc2" "640,900.74" "1" "1" "0")
(command "_insert" "blkuc2" "640,900.37" "1" "1" "180")
(command "_insert" "blkuc2" "640,901.11" "1" "1" "0")
(command "_insert" "blkuc2" "640,900.74" "1" "1" "180")
(command "_insert" "blkuc2" "640,901.48" "1" "1" "0")
(command "_insert" "blkuc2" "640,901.11" "1" "1" "180")
(command "_insert" "blkuc2" "640,901.85" "1" "1" "0")
(command "_insert" "blkuc2" "640,901.48" "1" "1" "180")
(command "_insert" "blkuc2" "640,902.22" "1" "1" "0")
(command "_insert" "blkuc2" "640,901.85" "1" "1" "180")
(command "_insert" "blkuc2" "640,902.59" "1" "1" "0")
(command "_insert" "blkuc2" "640,902.22" "1" "1" "180")
(command "_insert" "blkuc2" "640,902.96" "1" "1" "0")
(command "_insert" "blkuc2" "640,902.59" "1" "1" "180")
(command "_insert" "blkuc2" "640,903.33" "1" "1" "0")
(command "_insert" "blkuc2" "640,902.96" "1" "1" "180")
(command "_insert" "blkuc2" "640,903.7" "1" "1" "0")
(command "_insert" "blkuc2" "640,903.33" "1" "1" "180")
(command "_insert" "blkuc2" "640,904.07" "1" "1" "0")
(command "_insert" "blkuc2" "640,903.7" "1" "1" "180")
(command "_insert" "blkuc2" "640,904.44" "1" "1" "0")
(command "_insert" "blkuc2" "640,904.07" "1" "1" "180")
(command "_insert" "blkuc2" "640,904.81" "1" "1" "0")
(command "_insert" "blkuc2" "640,904.44" "1" "1" "180")
(command "_insert" "blkuc2" "640,905.18" "1" "1" "0")
(command "_insert" "blkuc2" "640,904.81" "1" "1" "180")
(command "_insert" "blkuc2" "640,905.55" "1" "1" "0")
(command "_insert" "blkuc2" "640,905.18" "1" "1" "180")
(command "_insert" "blkuc2" "640,905.92" "1" "1" "0")
(command "_insert" "blkuc2" "640,905.55" "1" "1" "180")
(command "_insert" "blkuc2" "640,906.29" "1" "1" "0")
(command "_insert" "blkuc2" "640,905.92" "1" "1" "180")
(command "_insert" "blkuc2" "640,906.66" "1" "1" "0")
(command "_insert" "blkuc2" "640,906.29" "1" "1" "180")
(command "_insert" "blkuc2" "640,907.03" "1" "1" "0")
(command "_insert" "blkuc2" "640,906.66" "1" "1" "180")
(command "_insert" "blkuc2" "640,907.4" "1" "1" "0")
(command "_insert" "blkuc2" "640,907.03" "1" "1" "180")
(command "_insert" "blkuc2" "640,907.77" "1" "1" "0")
(command "_insert" "blkuc2" "640,907.4" "1" "1" "180")
(command "_insert" "blkuc2" "640,908.14" "1" "1" "0")
(command "_insert" "blkuc2" "640,907.77" "1" "1" "180")
(command "_insert" "blkuc2" "640,908.51" "1" "1" "0")
(command "_insert" "blkuc2" "640,908.14" "1" "1" "180")
(command "_insert" "blkuc2" "640,908.88" "1" "1" "0")
(command "_insert" "blkuc2" "640,908.51" "1" "1" "180")
(command "_insert" "blkuc2" "640,909.25" "1" "1" "0")
(command "_insert" "blkuc2" "640,908.88" "1" "1" "180")
(command "_insert" "blkuc2" "640,909.62" "1" "1" "0")
(command "_insert" "blkuc2" "640,909.25" "1" "1" "180")
(command "_insert" "blkuc2" "640,909.99" "1" "1" "0")
(command "_insert" "blkuc2" "640,909.62" "1" "1" "180")
(command "_insert" "blkuc2" "640,910.36" "1" "1" "0")
(command "_insert" "blkuc2" "640,909.99" "1" "1" "180")
(command "_insert" "blkuc2" "640,910.73" "1" "1" "0")
(command "_insert" "blkuc2" "640,910.36" "1" "1" "180")
(command "_insert" "blkuc2" "640,911.1" "1" "1" "0")
(command "_insert" "blkuc2" "640,910.73" "1" "1" "180")
(command "_insert" "blkuc2" "640,911.47" "1" "1" "0")
(command "_insert" "blkuc2" "640,911.1" "1" "1" "180")
(command "_insert" "blkuc2" "640,911.84" "1" "1" "0")
(command "_insert" "blkuc2" "640,911.47" "1" "1" "180")
(command "_insert" "blkuc2" "640,912.21" "1" "1" "0")
(command "_insert" "blkuc2" "640,911.84" "1" "1" "180")
(command "_insert" "blkuc2" "640,912.58" "1" "1" "0")
(command "_insert" "blkuc2" "640,912.21" "1" "1" "180")
(command "_insert" "blkuc2" "640,912.95" "1" "1" "0")
(command "_insert" "blkuc2" "640,912.58" "1" "1" "180")
(command "_insert" "blkuc2" "640,913.32" "1" "1" "0")
(command "_insert" "blkuc2" "640,912.95" "1" "1" "180")
(command "_insert" "blkuc2" "640,913.69" "1" "1" "0")
(command "_insert" "blkuc2" "640,913.32" "1" "1" "180")
(command "_insert" "blkuc2" "640,914.06" "1" "1" "0")
(command "_insert" "blkuc2" "640,913.69" "1" "1" "180")
(command "_insert" "blkuc2" "640,914.43" "1" "1" "0")
(command "_insert" "blkuc2" "640,914.06" "1" "1" "180")
(command "_insert" "blkuc2" "640,914.8" "1" "1" "0")
(command "_insert" "blkuc2" "640,914.43" "1" "1" "180")
(command "_insert" "blkuc2" "640,915.17" "1" "1" "0")
(command "_insert" "blkuc2" "640,914.8" "1" "1" "180")
(command "_insert" "blkuc2" "640,915.54" "1" "1" "0")
(command "_insert" "blkuc2" "640,915.17" "1" "1" "180")
(command "_insert" "blkuc2" "640,915.91" "1" "1" "0")
(command "_insert" "blkuc2" "640,915.54" "1" "1" "180")
(command "_insert" "blkuc2" "640,916.28" "1" "1" "0")
(command "_insert" "blkuc2" "640,915.91" "1" "1" "180")
(command "_insert" "blkuc2" "640,916.65" "1" "1" "0")
(command "_insert" "blkuc2" "640,916.28" "1" "1" "180")
(command "_insert" "blkuc2" "640,917.02" "1" "1" "0")
(command "_insert" "blkuc2" "640,916.65" "1" "1" "180")
(command "_insert" "blkuc2" "640,917.39" "1" "1" "0")
(command "_insert" "blkuc2" "640,917.02" "1" "1" "180")
(command "_insert" "blkuc2" "640,917.76" "1" "1" "0")
(command "_insert" "blkuc2" "640,917.39" "1" "1" "180")
(command "_insert" "blkuc2" "640,918.13" "1" "1" "0")
(command "_insert" "blkuc2" "640,917.76" "1" "1" "180")
(command "_insert" "blkuc2" "640,918.5" "1" "1" "0")
(command "_insert" "blkuc2" "640,918.13" "1" "1" "180")
(command "_insert" "blkuc2" "640,918.87" "1" "1" "0")
(command "_insert" "blkuc2" "640,918.5" "1" "1" "180")
(command "_insert" "blkuc2" "640,919.24" "1" "1" "0")
(command "_insert" "blkuc2" "640,918.87" "1" "1" "180")
(command "_insert" "blkuc2" "640,919.61" "1" "1" "0")
(command "_insert" "blkuc2" "640,919.24" "1" "1" "180")
(command "_insert" "blkuc2" "640,919.98" "1" "1" "0")
(command "_insert" "blkuc2" "640,919.61" "1" "1" "180")
(command "_insert" "blkuc2" "640,920.35" "1" "1" "0")
(command "_insert" "blkuc2" "640,919.98" "1" "1" "180")
(command "_insert" "blkuc2" "640,920.72" "1" "1" "0")
(command "_insert" "blkuc2" "640,920.35" "1" "1" "180")
(command "_insert" "blkuc2" "640,921.09" "1" "1" "0")
(command "_insert" "blkuc2" "640,920.72" "1" "1" "180")
(command "_insert" "blkuc2" "640,921.46" "1" "1" "0")
(command "_insert" "blkuc2" "640,921.09" "1" "1" "180")
(command "_insert" "blkuc2" "640,921.83" "1" "1" "0")
(command "_insert" "blkuc2" "640,921.46" "1" "1" "180")
(command "_insert" "blkuc2" "640,922.2" "1" "1" "0")
(command "_insert" "blkuc2" "640,921.83" "1" "1" "180")
(command "_insert" "blkuc2" "640,922.57" "1" "1" "0")
(command "_insert" "blkuc2" "640,922.2" "1" "1" "180")
(command "_insert" "blkuc2" "640,922.94" "1" "1" "0")
(command "_insert" "blkuc2" "640,922.57" "1" "1" "180")
(command "_insert" "blkuc2" "640,923.31" "1" "1" "0")
(command "_insert" "blkuc2" "640,922.94" "1" "1" "180")
(command "_insert" "blkuc2" "640,923.68" "1" "1" "0")
(command "_insert" "blkuc2" "640,923.31" "1" "1" "180")
(command "_insert" "blkuc2" "640,924.05" "1" "1" "0")
(command "_insert" "blkuc2" "640,923.68" "1" "1" "180")
(command "_insert" "blkuc2" "640,924.42" "1" "1" "0")
(command "_insert" "blkuc2" "640,924.05" "1" "1" "180")
(command "_insert" "blkuc2" "640,924.79" "1" "1" "0")
(command "_insert" "blkuc2" "640,924.42" "1" "1" "180")
(command "_insert" "blkuc2" "640,925.16" "1" "1" "0")
(command "_insert" "blkuc2" "640,924.79" "1" "1" "180")
(command "_insert" "blkuc2" "640,925.53" "1" "1" "0")
(command "_insert" "blkuc2" "640,925.16" "1" "1" "180")
(command "_insert" "blkuc2" "640,925.9" "1" "1" "0")
(command "_insert" "blkuc2" "640,925.53" "1" "1" "180")
(command "_insert" "blkuc2" "640,926.27" "1" "1" "0")
(command "_insert" "blkuc2" "640,925.9" "1" "1" "180")
(command "_insert" "blkuc2" "640,926.64" "1" "1" "0")
(command "_insert" "blkuc2" "640,926.27" "1" "1" "180")
(command "_insert" "blkuc2" "640,927.01" "1" "1" "0")
(command "_insert" "blkuc2" "640,926.64" "1" "1" "180")
(command "_insert" "blkuc2" "640,927.38" "1" "1" "0")
(command "_insert" "blkuc2" "640,927.01" "1" "1" "180")
(command "_insert" "blkuc2" "640,927.75" "1" "1" "0")
(command "_insert" "blkuc2" "640,927.38" "1" "1" "180")
(command "_layer" "set" "phccover" "")
(command "_rectangle" "638.908,933.3" "641.092,866.7")
(command "_layer" "set" "nitride" "")
(setq phc2 currobj)
(command "_layer" "set" "cover" "")
(command "_rectangle" "638.908,836.7" "641.092,963.3")
(command "_layer" "set" "nitride" "")
(command "_layer" "set" "text" "")
(command "_circle" "637.958,846.7" "0.075")
(command "_circle" "637.583,846.7" "0.15")
(command "_circle" "637.208,846.7" "0.075")
(command "_circle" "636.833,846.7" "0.15")
(command "_circle" "637.958,848.7" "0.075")
(command "_circle" "637.583,848.7" "0.075")
(command "_circle" "637.208,848.7" "0.15")
(command "_circle" "636.833,848.7" "0.15")
(command "_circle" "637.958,850.7" "0.075")
(command "_circle" "637.583,850.7" "0.15")
(command "_circle" "637.208,850.7" "0.15")
(command "_circle" "636.833,850.7" "0.15")
(command "_circle" "637.958,852.7" "0.075")
(command "_circle" "637.583,852.7" "0.075")
(command "_circle" "637.208,852.7" "0.075")
(command "_circle" "636.833,852.7" "0.075")
(command "_circle" "636.458,852.7" "0.15")
(command "_circle" "637.958,854.7" "0.075")
(command "_circle" "637.583,854.7" "0.15")
(command "_circle" "637.208,854.7" "0.075")
(command "_circle" "636.833,854.7" "0.075")
(command "_circle" "636.458,854.7" "0.15")
(command "_circle" "637.958,856.7" "0.075")
(command "_circle" "637.583,856.7" "0.075")
(command "_circle" "637.208,856.7" "0.15")
(command "_circle" "636.833,856.7" "0.075")
(command "_circle" "636.458,856.7" "0.15")
(command "_circle" "637.958,858.7" "0.075")
(command "_circle" "637.583,858.7" "0.15")
(command "_circle" "637.208,858.7" "0.15")
(command "_circle" "636.833,858.7" "0.075")
(command "_circle" "636.458,858.7" "0.15")
(command "_circle" "637.958,860.7" "0.075")
(command "_circle" "637.583,860.7" "0.075")
(command "_circle" "637.208,860.7" "0.075")
(command "_circle" "636.833,860.7" "0.15")
(command "_circle" "636.458,860.7" "0.15")
(command "_circle" "637.958,862.7" "0.075")
(command "_circle" "637.583,862.7" "0.15")
(command "_circle" "637.208,862.7" "0.075")
(command "_circle" "636.833,862.7" "0.15")
(command "_circle" "636.458,862.7" "0.15")
(command "_circle" "637.958,864.7" "0.075")
(command "_circle" "637.583,864.7" "0.075")
(command "_circle" "637.208,864.7" "0.15")
(command "_circle" "636.833,864.7" "0.15")
(command "_circle" "636.458,864.7" "0.15")
(command "_circle" "637.958,866.7" "0.075")
(command "_circle" "637.583,866.7" "0.15")
(command "_circle" "637.208,866.7" "0.15")
(command "_circle" "636.833,866.7" "0.15")
(command "_circle" "636.458,866.7" "0.15")
(command "_circle" "637.958,868.7" "0.075")
(command "_circle" "637.583,868.7" "0.075")
(command "_circle" "637.208,868.7" "0.075")
(command "_circle" "636.833,868.7" "0.075")
(command "_circle" "636.458,868.7" "0.075")
(command "_circle" "636.083,868.7" "0.15")
(command "_circle" "637.958,870.7" "0.075")
(command "_circle" "637.583,870.7" "0.15")
(command "_circle" "637.208,870.7" "0.075")
(command "_circle" "636.833,870.7" "0.075")
(command "_circle" "636.458,870.7" "0.075")
(command "_circle" "636.083,870.7" "0.15")
(command "_circle" "637.958,872.7" "0.075")
(command "_circle" "637.583,872.7" "0.075")
(command "_circle" "637.208,872.7" "0.15")
(command "_circle" "636.833,872.7" "0.075")
(command "_circle" "636.458,872.7" "0.075")
(command "_circle" "636.083,872.7" "0.15")
(command "_circle" "637.958,874.7" "0.075")
(command "_circle" "637.583,874.7" "0.15")
(command "_circle" "637.208,874.7" "0.15")
(command "_circle" "636.833,874.7" "0.075")
(command "_circle" "636.458,874.7" "0.075")
(command "_circle" "636.083,874.7" "0.15")
(command "_circle" "637.958,876.7" "0.075")
(command "_circle" "637.583,876.7" "0.075")
(command "_circle" "637.208,876.7" "0.075")
(command "_circle" "636.833,876.7" "0.15")
(command "_circle" "636.458,876.7" "0.075")
(command "_circle" "636.083,876.7" "0.15")
(command "_circle" "637.958,878.7" "0.075")
(command "_circle" "637.583,878.7" "0.15")
(command "_circle" "637.208,878.7" "0.075")
(command "_circle" "636.833,878.7" "0.15")
(command "_circle" "636.458,878.7" "0.075")
(command "_circle" "636.083,878.7" "0.15")
(command "_circle" "637.958,880.7" "0.075")
(command "_circle" "637.583,880.7" "0.075")
(command "_circle" "637.208,880.7" "0.15")
(command "_circle" "636.833,880.7" "0.15")
(command "_circle" "636.458,880.7" "0.075")
(command "_circle" "636.083,880.7" "0.15")
(command "_circle" "637.958,882.7" "0.075")
(command "_circle" "637.583,882.7" "0.15")
(command "_circle" "637.208,882.7" "0.15")
(command "_circle" "636.833,882.7" "0.15")
(command "_circle" "636.458,882.7" "0.075")
(command "_circle" "636.083,882.7" "0.15")
(command "_circle" "637.958,884.7" "0.075")
(command "_circle" "637.583,884.7" "0.075")
(command "_circle" "637.208,884.7" "0.075")
(command "_circle" "636.833,884.7" "0.075")
(command "_circle" "636.458,884.7" "0.15")
(command "_circle" "636.083,884.7" "0.15")
(command "_circle" "637.958,886.7" "0.075")
(command "_circle" "637.583,886.7" "0.15")
(command "_circle" "637.208,886.7" "0.075")
(command "_circle" "636.833,886.7" "0.075")
(command "_circle" "636.458,886.7" "0.15")
(command "_circle" "636.083,886.7" "0.15")
(command "_circle" "637.958,888.7" "0.075")
(command "_circle" "637.583,888.7" "0.075")
(command "_circle" "637.208,888.7" "0.15")
(command "_circle" "636.833,888.7" "0.075")
(command "_circle" "636.458,888.7" "0.15")
(command "_circle" "636.083,888.7" "0.15")
(command "_circle" "637.958,890.7" "0.075")
(command "_circle" "637.583,890.7" "0.15")
(command "_circle" "637.208,890.7" "0.15")
(command "_circle" "636.833,890.7" "0.075")
(command "_circle" "636.458,890.7" "0.15")
(command "_circle" "636.083,890.7" "0.15")
(command "_circle" "637.958,892.7" "0.075")
(command "_circle" "637.583,892.7" "0.075")
(command "_circle" "637.208,892.7" "0.075")
(command "_circle" "636.833,892.7" "0.15")
(command "_circle" "636.458,892.7" "0.15")
(command "_circle" "636.083,892.7" "0.15")
(command "_circle" "637.958,894.7" "0.075")
(command "_circle" "637.583,894.7" "0.15")
(command "_circle" "637.208,894.7" "0.075")
(command "_circle" "636.833,894.7" "0.15")
(command "_circle" "636.458,894.7" "0.15")
(command "_circle" "636.083,894.7" "0.15")
(command "_circle" "637.958,896.7" "0.075")
(command "_circle" "637.583,896.7" "0.075")
(command "_circle" "637.208,896.7" "0.15")
(command "_circle" "636.833,896.7" "0.15")
(command "_circle" "636.458,896.7" "0.15")
(command "_circle" "636.083,896.7" "0.15")
(command "_circle" "637.958,898.7" "0.075")
(command "_circle" "637.583,898.7" "0.15")
(command "_circle" "637.208,898.7" "0.15")
(command "_circle" "636.833,898.7" "0.15")
(command "_circle" "636.458,898.7" "0.15")
(command "_circle" "636.083,898.7" "0.15")
(command "_circle" "637.958,900.7" "0.075")
(command "_circle" "637.583,900.7" "0.075")
(command "_circle" "637.208,900.7" "0.075")
(command "_circle" "636.833,900.7" "0.075")
(command "_circle" "636.458,900.7" "0.075")
(command "_circle" "636.083,900.7" "0.075")
(command "_circle" "635.708,900.7" "0.15")
(command "_circle" "637.958,902.7" "0.075")
(command "_circle" "637.583,902.7" "0.15")
(command "_circle" "637.208,902.7" "0.075")
(command "_circle" "636.833,902.7" "0.075")
(command "_circle" "636.458,902.7" "0.075")
(command "_circle" "636.083,902.7" "0.075")
(command "_circle" "635.708,902.7" "0.15")
(command "_circle" "637.958,904.7" "0.075")
(command "_circle" "637.583,904.7" "0.075")
(command "_circle" "637.208,904.7" "0.15")
(command "_circle" "636.833,904.7" "0.075")
(command "_circle" "636.458,904.7" "0.075")
(command "_circle" "636.083,904.7" "0.075")
(command "_circle" "635.708,904.7" "0.15")
(command "_circle" "637.958,906.7" "0.075")
(command "_circle" "637.583,906.7" "0.15")
(command "_circle" "637.208,906.7" "0.15")
(command "_circle" "636.833,906.7" "0.075")
(command "_circle" "636.458,906.7" "0.075")
(command "_circle" "636.083,906.7" "0.075")
(command "_circle" "635.708,906.7" "0.15")
(command "_circle" "637.958,908.7" "0.075")
(command "_circle" "637.583,908.7" "0.075")
(command "_circle" "637.208,908.7" "0.075")
(command "_circle" "636.833,908.7" "0.15")
(command "_circle" "636.458,908.7" "0.075")
(command "_circle" "636.083,908.7" "0.075")
(command "_circle" "635.708,908.7" "0.15")
(command "_circle" "637.958,910.7" "0.075")
(command "_circle" "637.583,910.7" "0.15")
(command "_circle" "637.208,910.7" "0.075")
(command "_circle" "636.833,910.7" "0.15")
(command "_circle" "636.458,910.7" "0.075")
(command "_circle" "636.083,910.7" "0.075")
(command "_circle" "635.708,910.7" "0.15")
(command "_circle" "637.958,912.7" "0.075")
(command "_circle" "637.583,912.7" "0.075")
(command "_circle" "637.208,912.7" "0.15")
(command "_circle" "636.833,912.7" "0.15")
(command "_circle" "636.458,912.7" "0.075")
(command "_circle" "636.083,912.7" "0.075")
(command "_circle" "635.708,912.7" "0.15")
(command "_circle" "637.958,914.7" "0.075")
(command "_circle" "637.583,914.7" "0.15")
(command "_circle" "637.208,914.7" "0.15")
(command "_circle" "636.833,914.7" "0.15")
(command "_circle" "636.458,914.7" "0.075")
(command "_circle" "636.083,914.7" "0.075")
(command "_circle" "635.708,914.7" "0.15")
(command "_circle" "637.958,916.7" "0.075")
(command "_circle" "637.583,916.7" "0.075")
(command "_circle" "637.208,916.7" "0.075")
(command "_circle" "636.833,916.7" "0.075")
(command "_circle" "636.458,916.7" "0.15")
(command "_circle" "636.083,916.7" "0.075")
(command "_circle" "635.708,916.7" "0.15")
(command "_circle" "637.958,918.7" "0.075")
(command "_circle" "637.583,918.7" "0.15")
(command "_circle" "637.208,918.7" "0.075")
(command "_circle" "636.833,918.7" "0.075")
(command "_circle" "636.458,918.7" "0.15")
(command "_circle" "636.083,918.7" "0.075")
(command "_circle" "635.708,918.7" "0.15")
(command "_circle" "637.958,920.7" "0.075")
(command "_circle" "637.583,920.7" "0.075")
(command "_circle" "637.208,920.7" "0.15")
(command "_circle" "636.833,920.7" "0.075")
(command "_circle" "636.458,920.7" "0.15")
(command "_circle" "636.083,920.7" "0.075")
(command "_circle" "635.708,920.7" "0.15")
(command "_circle" "637.958,922.7" "0.075")
(command "_circle" "637.583,922.7" "0.15")
(command "_circle" "637.208,922.7" "0.15")
(command "_circle" "636.833,922.7" "0.075")
(command "_circle" "636.458,922.7" "0.15")
(command "_circle" "636.083,922.7" "0.075")
(command "_circle" "635.708,922.7" "0.15")
(command "_circle" "637.958,924.7" "0.075")
(command "_circle" "637.583,924.7" "0.075")
(command "_circle" "637.208,924.7" "0.075")
(command "_circle" "636.833,924.7" "0.15")
(command "_circle" "636.458,924.7" "0.15")
(command "_circle" "636.083,924.7" "0.075")
(command "_circle" "635.708,924.7" "0.15")
(command "_circle" "637.958,926.7" "0.075")
(command "_circle" "637.583,926.7" "0.15")
(command "_circle" "637.208,926.7" "0.075")
(command "_circle" "636.833,926.7" "0.15")
(command "_circle" "636.458,926.7" "0.15")
(command "_circle" "636.083,926.7" "0.075")
(command "_circle" "635.708,926.7" "0.15")
(command "_circle" "637.958,928.7" "0.075")
(command "_circle" "637.583,928.7" "0.075")
(command "_circle" "637.208,928.7" "0.15")
(command "_circle" "636.833,928.7" "0.15")
(command "_circle" "636.458,928.7" "0.15")
(command "_circle" "636.083,928.7" "0.075")
(command "_circle" "635.708,928.7" "0.15")
(command "_circle" "637.958,930.7" "0.075")
(command "_circle" "637.583,930.7" "0.15")
(command "_circle" "637.208,930.7" "0.15")
(command "_circle" "636.833,930.7" "0.15")
(command "_circle" "636.458,930.7" "0.15")
(command "_circle" "636.083,930.7" "0.075")
(command "_circle" "635.708,930.7" "0.15")
(command "_circle" "637.958,932.7" "0.075")
(command "_circle" "637.583,932.7" "0.075")
(command "_circle" "637.208,932.7" "0.075")
(command "_circle" "636.833,932.7" "0.075")
(command "_circle" "636.458,932.7" "0.075")
(command "_circle" "636.083,932.7" "0.15")
(command "_circle" "635.708,932.7" "0.15")
(command "_circle" "637.958,934.7" "0.075")
(command "_circle" "637.583,934.7" "0.15")
(command "_circle" "637.208,934.7" "0.075")
(command "_circle" "636.833,934.7" "0.075")
(command "_circle" "636.458,934.7" "0.075")
(command "_circle" "636.083,934.7" "0.15")
(command "_circle" "635.708,934.7" "0.15")
(command "_circle" "637.958,936.7" "0.075")
(command "_circle" "637.583,936.7" "0.075")
(command "_circle" "637.208,936.7" "0.15")
(command "_circle" "636.833,936.7" "0.075")
(command "_circle" "636.458,936.7" "0.075")
(command "_circle" "636.083,936.7" "0.15")
(command "_circle" "635.708,936.7" "0.15")
(command "_circle" "637.958,938.7" "0.075")
(command "_circle" "637.583,938.7" "0.15")
(command "_circle" "637.208,938.7" "0.15")
(command "_circle" "636.833,938.7" "0.075")
(command "_circle" "636.458,938.7" "0.075")
(command "_circle" "636.083,938.7" "0.15")
(command "_circle" "635.708,938.7" "0.15")
(command "_circle" "637.958,940.7" "0.075")
(command "_circle" "637.583,940.7" "0.075")
(command "_circle" "637.208,940.7" "0.075")
(command "_circle" "636.833,940.7" "0.15")
(command "_circle" "636.458,940.7" "0.075")
(command "_circle" "636.083,940.7" "0.15")
(command "_circle" "635.708,940.7" "0.15")
(command "_circle" "637.958,942.7" "0.075")
(command "_circle" "637.583,942.7" "0.15")
(command "_circle" "637.208,942.7" "0.075")
(command "_circle" "636.833,942.7" "0.15")
(command "_circle" "636.458,942.7" "0.075")
(command "_circle" "636.083,942.7" "0.15")
(command "_circle" "635.708,942.7" "0.15")
(command "_circle" "637.958,944.7" "0.075")
(command "_circle" "637.583,944.7" "0.075")
(command "_circle" "637.208,944.7" "0.15")
(command "_circle" "636.833,944.7" "0.15")
(command "_circle" "636.458,944.7" "0.075")
(command "_circle" "636.083,944.7" "0.15")
(command "_circle" "635.708,944.7" "0.15")
(command "_circle" "637.958,946.7" "0.075")
(command "_circle" "637.583,946.7" "0.15")
(command "_circle" "637.208,946.7" "0.15")
(command "_circle" "636.833,946.7" "0.15")
(command "_circle" "636.458,946.7" "0.075")
(command "_circle" "636.083,946.7" "0.15")
(command "_circle" "635.708,946.7" "0.15")
(command "_circle" "637.958,948.7" "0.075")
(command "_circle" "637.583,948.7" "0.075")
(command "_circle" "637.208,948.7" "0.075")
(command "_circle" "636.833,948.7" "0.075")
(command "_circle" "636.458,948.7" "0.15")
(command "_circle" "636.083,948.7" "0.15")
(command "_circle" "635.708,948.7" "0.15")
(command "_circle" "637.958,950.7" "0.075")
(command "_circle" "637.583,950.7" "0.15")
(command "_circle" "637.208,950.7" "0.075")
(command "_circle" "636.833,950.7" "0.075")
(command "_circle" "636.458,950.7" "0.15")
(command "_circle" "636.083,950.7" "0.15")
(command "_circle" "635.708,950.7" "0.15")
(command "_circle" "637.958,952.7" "0.075")
(command "_circle" "637.583,952.7" "0.075")
(command "_circle" "637.208,952.7" "0.15")
(command "_circle" "636.833,952.7" "0.075")
(command "_circle" "636.458,952.7" "0.15")
(command "_circle" "636.083,952.7" "0.15")
(command "_circle" "635.708,952.7" "0.15")
(command "_circle" "637.958,954.7" "0.075")
(command "_circle" "637.583,954.7" "0.15")
(command "_circle" "637.208,954.7" "0.15")
(command "_circle" "636.833,954.7" "0.075")
(command "_circle" "636.458,954.7" "0.15")
(command "_circle" "636.083,954.7" "0.15")
(command "_circle" "635.708,954.7" "0.15")
(command "_circle" "637.958,956.7" "0.075")
(command "_circle" "637.583,956.7" "0.075")
(command "_circle" "637.208,956.7" "0.075")
(command "_circle" "636.833,956.7" "0.15")
(command "_circle" "636.458,956.7" "0.15")
(command "_circle" "636.083,956.7" "0.15")
(command "_circle" "635.708,956.7" "0.15")
(command "_circle" "637.958,958.7" "0.075")
(command "_circle" "637.583,958.7" "0.15")
(command "_circle" "637.208,958.7" "0.075")
(command "_circle" "636.833,958.7" "0.15")
(command "_circle" "636.458,958.7" "0.15")
(command "_circle" "636.083,958.7" "0.15")
(command "_circle" "635.708,958.7" "0.15")
(command "_circle" "637.958,960.7" "0.075")
(command "_circle" "637.583,960.7" "0.075")
(command "_circle" "637.208,960.7" "0.15")
(command "_circle" "636.833,960.7" "0.15")
(command "_circle" "636.458,960.7" "0.15")
(command "_circle" "636.083,960.7" "0.15")
(command "_circle" "635.708,960.7" "0.15")
(command "_circle" "637.958,962.7" "0.075")
(command "_circle" "637.583,962.7" "0.15")
(command "_circle" "637.208,962.7" "0.15")
(command "_circle" "636.833,962.7" "0.15")
(command "_circle" "636.458,962.7" "0.15")
(command "_circle" "636.083,962.7" "0.15")
(command "_circle" "635.708,962.7" "0.15")
(command "_layer" "set" "nitride" "")
(command "_layer" "set" "text" "")
(command-s "_text" "626.908,963.3" "2" "-90" "a = 370 nm" )
(sssetfirst nil (ssget "_L"))
(if (not (numberp (vl-string-search "Mac" (getvar "platform")))) (c:txtexp))
(command "_layer" "set" "nitride" "")
(command "_layer" "set" "text" "")
(command-s "_text" "623.908,963.3" "2" "-90" "gap = 250 nm" )
(sssetfirst nil (ssget "_L"))
(if (not (numberp (vl-string-search "Mac" (getvar "platform")))) (c:txtexp))
(command "_layer" "set" "nitride" "")
(command "_layer" "set" "text" "")
(command-s "_text" "620.908,963.3" "2" "-90" "amplitude = 132 nm" )
(sssetfirst nil (ssget "_L"))
(if (not (numberp (vl-string-search "Mac" (getvar "platform")))) (c:txtexp))
(command "_layer" "set" "nitride" "")
(command "_layer" "set" "text" "")
(command-s "_text" "617.908,963.3" "2" "-90" "start width = 280 nm" )
(sssetfirst nil (ssget "_L"))
(if (not (numberp (vl-string-search "Mac" (getvar "platform")))) (c:txtexp))
(command "_layer" "set" "nitride" "")
(command "_layer" "set" "text" "")
(command-s "_text" "614.908,963.3" "2" "-90" "width = 289 nm" )
(sssetfirst nil (ssget "_L"))
(if (not (numberp (vl-string-search "Mac" (getvar "platform")))) (c:txtexp))
(command "_layer" "set" "nitride" "")
(command "_layer" "set" "text" "")
(command-s "_text" "611.908,963.3" "2" "-90" "taper: 15" )
(sssetfirst nil (ssget "_L"))
(if (not (numberp (vl-string-search "Mac" (getvar "platform")))) (c:txtexp))
(command "_layer" "set" "nitride" "")
(command "_layer" "set" "text" "")
(command-s "_text" "608.908,963.3" "2" "-90" "nominal: 150" )
(sssetfirst nil (ssget "_L"))
(if (not (numberp (vl-string-search "Mac" (getvar "platform")))) (c:txtexp))
(command "_layer" "set" "nitride" "")
(command "_layer" "set" "indicators" "")
(setq coords (list 
(list 560.415 940) 
(list 560.415 920) 
(list 540.415 900) 
(list 560.415 880) 
(list 560.415 860) 
(list 560.415 900) 
(list 560.415 887.0711) 
(list 547.4861 900) 
(list 560.415 912.9289) 
(list 560.415 900)))
(apply 'command (append '("pline") coords '("c")))
(command "._fillet" "radius" "1" "._fillet" "P" (entlast))
(setq coords (list 
(list 719.585 940) 
(list 719.585 920) 
(list 739.585 900) 
(list 719.585 880) 
(list 719.585 860) 
(list 719.585 900) 
(list 719.585 887.0711) 
(list 732.5139 900) 
(list 719.585 912.9289) 
(list 719.585 900)))
(apply 'command (append '("pline") coords '("c")))
(command "._fillet" "radius" "1" "._fillet" "P" (entlast))
(command "_layer" "set" "holes" "")
(command "_circle" "558.0629,914.1124" "0.5")
(command "_circle" "555.7109,911.7603" "0.5")
(command "_circle" "553.3588,909.4083" "0.5")
(command "_circle" "551.0067,907.0562" "0.5")
(command "_circle" "548.6547,904.7041" "0.5")
(command "_circle" "546.3026,902.3521" "0.5")
(command "_circle" "543.9505,900" "0.5")
(command "_circle" "546.3026,897.6479" "0.5")
(command "_circle" "548.6547,895.2959" "0.5")
(command "_circle" "551.0067,892.9438" "0.5")
(command "_circle" "553.3588,890.5917" "0.5")
(command "_circle" "555.7109,888.2397" "0.5")
(command "_circle" "558.0629,885.8876" "0.5")
(command "_circle" "721.9371,914.1124" "0.5")
(command "_circle" "724.2891,911.7603" "0.5")
(command "_circle" "726.6412,909.4083" "0.5")
(command "_circle" "728.9933,907.0562" "0.5")
(command "_circle" "731.3453,904.7041" "0.5")
(command "_circle" "733.6974,902.3521" "0.5")
(command "_circle" "736.0495,900" "0.5")
(command "_circle" "733.6974,897.6479" "0.5")
(command "_circle" "731.3453,895.2959" "0.5")
(command "_circle" "728.9933,892.9438" "0.5")
(command "_circle" "726.6412,890.5917" "0.5")
(command "_circle" "724.2891,888.2397" "0.5")
(command "_circle" "721.9371,885.8876" "0.5")
(command "_layer" "set" "nitride" "")
(command "_block" "blkcoupler2" "640,900" coupler2 "")
(command "_insert" "blkcoupler2" "640,900" "1" "1" "0")
(command "_insert" "blkcoupler2" "640,900" "1" "1" "180")
(command "_block" "blksinglenanobeam2" "640,900" singlenanobeam2 "")
(command "_insert" "blksinglenanobeam2" "640,900" "1" "1" "0")
(command "_insert" "blksinglenanobeam2" "640,900" "1" "1" "180")
(command "_block" "blkanglednodearray2" "640,900" anglednodearray2 "")
(command "_insert" "blkanglednodearray2" "640,900" "1" "1" "0")
(command "_insert" "blkanglednodearray2" "640,900" "1" "1" "180")
(command "_block" "blkcooledsinglenanobeam2" "640,900" cooledsinglenanobeam2 "")
(command "_insert" "blkcooledsinglenanobeam2" "640,900" "1" "1" "0")
(command "_insert" "blkcooledsinglenanobeam2" "640,900" "1" "1" "180")
(command "_block" "blkyjunction2" "640,900" yjunction2 "")
(command "_insert" "blkyjunction2" "640,900" "1" "1" "0")
(command "_insert" "blkyjunction2" "640,900" "1" "1" "180")
; DRAWING BULGING VEE GROOVE
(command "_layer" "set" "vgroove" "")
(setq coords (list 
(list 565.415 -605) 
(list 565.415 0) 
(list 565.415 0) 
(list 565.415 1800) 
(list 565.415 1800) 
(list 565.415 2405) 
(list 714.585 2405) 
(list 714.585 1800) 
(list 714.585 1800) 
(list 714.585 0) 
(list 714.585 0) 
(list 714.585 -605)))
(apply 'command (append '("pline") coords '("c")))
(command "._fillet" "radius" "0" "._fillet" "P" (entlast))
(command "_layer" "set" "window" "")
(command "_rectangle" "565.415,-1935" "714.585,-600")
(command "_rectangle" "565.415,2400" "714.585,5300")
(command "_layer" "set" "grid" "")
(command "_rectangle" "566.415,-1934" "589.9433,-1909.2133")
(command "_array" "last" "" "R" "75" "3" "25.7867" "24.5283")
(command "_rectangle" "641,-1934" "664.5283,-1909.2133")
(command "_array" "last" "" "R" "75" "3" "25.7867" "24.5283")
(command "_rectangle" "566.415,1" "589.9433,25.7")
(command "_array" "last" "" "R" "70" "3" "25.7" "24.5283")
(command "_rectangle" "641,1" "664.5283,25.7")
(command "_array" "last" "" "R" "70" "3" "25.7" "24.5283")
(command "_rectangle" "566.415,1801" "589.9433,1825.9185")
(command "_array" "last" "" "R" "135" "3" "25.9185" "24.5283")
(command "_rectangle" "641,1801" "664.5283,1825.9185")
(command "_array" "last" "" "R" "135" "3" "25.9185" "24.5283")
(command "_layer" "set" "vgrooveFDA" "")
(command "_rectangle" "714.585,-2233" "565.415,-1933")
(command "_layer" "set" "nitride" "")
(command "_layer" "set" "holes" "")
(command "_circle" "717.085,331.5" "0.5")
(command "_array" "last" "" "R" "379" "1" "3" "2.5")
(command "_circle" "562.915,331.5" "0.5")
(command "_array" "last" "" "R" "379" "1" "3" "-2.5")
(command "_layer" "set" "nitride" "")
(command "_layer" "set" "window" "")
(command "_layer" "set" "window" "")
(command "_rectangle" "719.585,0" "880.415,1800")
(command "._fillet" "radius" "20" "._fillet" "P" (entlast))
(command "_layer" "set" "grid" "")
(command "_rectangle" "720.585,1" "742.4179,25.7")
(command "_array" "last" "" "R" "70" "7" "25.7" "22.8329")
(command "_layer" "set" "nitride" "")
; DRAWING REGION LAYER
(command "_layer" "set" "regionLayer2" "")
(command "_rectangle" "560,-460" "720,2260")
(command "_layer" "set" "nitride" "")
(setq coupler2 nil)
(setq singlenanobeam2 nil)
(setq anglednodearray2 nil)
(setq cooledsinglenanobeam2 nil)
(setq yjunction2 nil)
; DEVICE #3
(command "_layer" "set" "window" "")
(command "_circle" "872.915,-415" "5")
(command "_circle" "872.915,-402.5" "5")
(command "_circle" "872.915,-390" "5")
(command "_layer" "set" "nitride" "")
(setq currobj nil)
(setq currobj (ssadd))
; DRAWING COUPLER
(setq coords (list 
(list 960.0615 -415) 
(list 960.0615 -413) 
(list 1033.585 -413) 
(list 1033.585 -413) 
(list 1033.9677 -413.0761) 
(list 1034.2921 -413.2929) 
(list 1034.5089 -413.6173) 
(list 1034.585 -414) 
(list 1034.585 -411.8) 
(list 1034.585 -411.8) 
(list 1034.5089 -412.1827) 
(list 1034.2921 -412.5071) 
(list 1033.9677 -412.7239) 
(list 1033.585 -412.8) 
(list 960.0615 -412.8) 
(list 960.0615 -410.8) 
(list 959.9385 -410.8) 
(list 959.9385 -412.8) 
(list 886.415 -412.8) 
(list 886.0323 -412.7239) 
(list 885.7079 -412.5071) 
(list 885.4911 -412.1827) 
(list 885.415 -411.8) 
(list 885.415 -411.8) 
(list 885.415 -414) 
(list 885.4911 -413.6173) 
(list 885.7079 -413.2929) 
(list 886.0323 -413.0761) 
(list 886.415 -413) 
(list 886.415 -413) 
(list 959.9385 -413) 
(list 959.9385 -415)))
(apply 'command (append '("pline") coords '("c")))
(setq currobj (ssadd (entlast) currobj))
(command "._fillet" "radius" "0.3" "._fillet" "P" (entlast))
(command "_layer" "set" "holes" "")
(command "_circle" "960,-412.9" "0.113")
(setq currobj (ssadd (entlast) currobj))
(command "_layer" "set" "nitride" "")
(command "_layer" "set" "text" "")
(command "_circle" "959.2,-415" "0.075")
(command "_circle" "959.2,-414.7" "0.075")
(command "_circle" "959.2,-414.4" "0.075")
(command "_circle" "958.9,-415" "0.075")
(command "_circle" "958.9,-414.7" "0.075")
(command "_circle" "958.9,-414.4" "0.075")
(command "_circle" "958.6,-415" "0.075")
(command "_circle" "958.6,-414.7" "0.075")
(command "_circle" "958.6,-414.4" "0.075")
(command "_layer" "set" "nitride" "")
(command "_layer" "set" "prebias" "")
(command "_rectangle" "885.415,-414" "1034.585,-411.8")
(setq currobj (ssadd (entlast) currobj))
(command "_rectangle" "959.9385,-415" "960.0615,-410.8")
(setq currobj (ssadd (entlast) currobj))
(command "_layer" "set" "nitride" "")
(setq coupler3 currobj)
(setq currobj nil)
(setq currobj (ssadd))
; DRAWING SINGLE NANOBEAM
(setq coords (list 
(list 960.0615 -410.8) 
(list 960.0615 -409.1417) 
(list 960.0615 -407.4833) 
(list 960.0615 -405.825) 
(list 960.0615 -404.1667) 
(list 960.0615 -402.5083) 
(list 960.0615 -400.85) 
(list 960.0615 -399.1917) 
(list 960.0615 -397.5333) 
(list 960.0616 -395.875) 
(list 960.0616 -394.2167) 
(list 960.0616 -392.5583) 
(list 960.0616 -390.9) 
(list 960.0617 -389.2417) 
(list 960.0617 -387.5833) 
(list 960.0617 -385.925) 
(list 960.0618 -384.2667) 
(list 960.0619 -382.6083) 
(list 960.0619 -380.95) 
(list 960.062 -379.2917) 
(list 960.0621 -377.6333) 
(list 960.0622 -375.975) 
(list 960.0623 -374.3167) 
(list 960.0624 -372.6583) 
(list 960.0625 -371) 
(list 960.0626 -369.3417) 
(list 960.0628 -367.6833) 
(list 960.0629 -366.025) 
(list 960.0631 -364.3667) 
(list 960.0632 -362.7083) 
(list 960.0634 -361.05) 
(list 960.0636 -359.3917) 
(list 960.0638 -357.7333) 
(list 960.0641 -356.075) 
(list 960.0643 -354.4167) 
(list 960.0646 -352.7583) 
(list 960.0648 -351.1) 
(list 960.0651 -349.4417) 
(list 960.0654 -347.7833) 
(list 960.0657 -346.125) 
(list 960.0661 -344.4667) 
(list 960.0664 -342.8083) 
(list 960.0668 -341.15) 
(list 960.0672 -339.4917) 
(list 960.0676 -337.8333) 
(list 960.068 -336.175) 
(list 960.0685 -334.5167) 
(list 960.0689 -332.8583) 
(list 960.0694 -331.2) 
(list 960.0699 -329.5417) 
(list 960.0704 -327.8833) 
(list 960.071 -326.225) 
(list 960.0715 -324.5667) 
(list 960.0721 -322.9083) 
(list 960.0728 -321.25) 
(list 960.0734 -319.5917) 
(list 960.0741 -317.9333) 
(list 960.0747 -316.275) 
(list 960.0754 -314.6167) 
(list 960.0762 -312.9583) 
(list 960.0769 -311.3) 
(list 960.0777 -309.6417) 
(list 960.0785 -307.9833) 
(list 960.0794 -306.325) 
(list 960.0802 -304.6667) 
(list 960.0811 -303.0083) 
(list 960.082 -301.35) 
(list 960.083 -299.6917) 
(list 960.084 -298.0333) 
(list 960.085 -296.375) 
(list 960.086 -294.7167) 
(list 960.0871 -293.0583) 
(list 960.0882 -291.4) 
(list 960.0893 -289.7417) 
(list 960.0905 -288.0833) 
(list 960.0917 -286.425) 
(list 960.0929 -284.7667) 
(list 960.0941 -283.1083) 
(list 960.0954 -281.45) 
(list 960.0967 -279.7917) 
(list 960.0981 -278.1333) 
(list 960.0995 -276.475) 
(list 960.1009 -274.8167) 
(list 960.1024 -273.1583) 
(list 960.1039 -271.5) 
(list 960.1054 -269.8417) 
(list 960.107 -268.1833) 
(list 960.1086 -266.525) 
(list 960.1102 -264.8667) 
(list 960.1119 -263.2083) 
(list 960.1136 -261.55) 
(list 960.1154 -259.8917) 
(list 960.1172 -258.2333) 
(list 960.119 -256.575) 
(list 960.1209 -254.9167) 
(list 960.1228 -253.2583) 
(list 960.1247 -251.6) 
(list 960.1267 -249.9417) 
(list 960.1288 -248.2833) 
(list 960.1308 -246.625) 
(list 960.133 -244.9667) 
(list 960.1351 -243.3083) 
(list 960.1373 -241.65) 
(list 960.1396 -239.9917) 
(list 960.1419 -238.3333) 
(list 960.1442 -236.675) 
(list 960.1466 -235.0167) 
(list 960.1491 -233.3583) 
(list 960.1515 -231.7) 
(list 960.1541 -230.0417) 
(list 960.1566 -228.3833) 
(list 960.1592 -226.725) 
(list 960.1619 -225.0667) 
(list 960.1646 -223.4083) 
(list 960.1674 -221.75) 
(list 960.1702 -220.0917) 
(list 960.1731 -218.4333) 
(list 960.176 -216.775) 
(list 960.1789 -215.1167) 
(list 960.1819 -213.4583) 
(list 960.185 -211.8) 
(list 959.815 -211.8) 
(list 959.8181 -213.4583) 
(list 959.8211 -215.1167) 
(list 959.824 -216.775) 
(list 959.8269 -218.4333) 
(list 959.8298 -220.0917) 
(list 959.8326 -221.75) 
(list 959.8354 -223.4083) 
(list 959.8381 -225.0667) 
(list 959.8408 -226.725) 
(list 959.8434 -228.3833) 
(list 959.8459 -230.0417) 
(list 959.8485 -231.7) 
(list 959.8509 -233.3583) 
(list 959.8534 -235.0167) 
(list 959.8558 -236.675) 
(list 959.8581 -238.3333) 
(list 959.8604 -239.9917) 
(list 959.8627 -241.65) 
(list 959.8649 -243.3083) 
(list 959.867 -244.9667) 
(list 959.8692 -246.625) 
(list 959.8712 -248.2833) 
(list 959.8733 -249.9417) 
(list 959.8753 -251.6) 
(list 959.8772 -253.2583) 
(list 959.8791 -254.9167) 
(list 959.881 -256.575) 
(list 959.8828 -258.2333) 
(list 959.8846 -259.8917) 
(list 959.8864 -261.55) 
(list 959.8881 -263.2083) 
(list 959.8898 -264.8667) 
(list 959.8914 -266.525) 
(list 959.893 -268.1833) 
(list 959.8946 -269.8417) 
(list 959.8961 -271.5) 
(list 959.8976 -273.1583) 
(list 959.8991 -274.8167) 
(list 959.9005 -276.475) 
(list 959.9019 -278.1333) 
(list 959.9033 -279.7917) 
(list 959.9046 -281.45) 
(list 959.9059 -283.1083) 
(list 959.9071 -284.7667) 
(list 959.9083 -286.425) 
(list 959.9095 -288.0833) 
(list 959.9107 -289.7417) 
(list 959.9118 -291.4) 
(list 959.9129 -293.0583) 
(list 959.914 -294.7167) 
(list 959.915 -296.375) 
(list 959.916 -298.0333) 
(list 959.917 -299.6917) 
(list 959.918 -301.35) 
(list 959.9189 -303.0083) 
(list 959.9198 -304.6667) 
(list 959.9206 -306.325) 
(list 959.9215 -307.9833) 
(list 959.9223 -309.6417) 
(list 959.9231 -311.3) 
(list 959.9238 -312.9583) 
(list 959.9246 -314.6167) 
(list 959.9253 -316.275) 
(list 959.9259 -317.9333) 
(list 959.9266 -319.5917) 
(list 959.9272 -321.25) 
(list 959.9279 -322.9083) 
(list 959.9285 -324.5667) 
(list 959.929 -326.225) 
(list 959.9296 -327.8833) 
(list 959.9301 -329.5417) 
(list 959.9306 -331.2) 
(list 959.9311 -332.8583) 
(list 959.9315 -334.5167) 
(list 959.932 -336.175) 
(list 959.9324 -337.8333) 
(list 959.9328 -339.4917) 
(list 959.9332 -341.15) 
(list 959.9336 -342.8083) 
(list 959.9339 -344.4667) 
(list 959.9343 -346.125) 
(list 959.9346 -347.7833) 
(list 959.9349 -349.4417) 
(list 959.9352 -351.1) 
(list 959.9354 -352.7583) 
(list 959.9357 -354.4167) 
(list 959.9359 -356.075) 
(list 959.9362 -357.7333) 
(list 959.9364 -359.3917) 
(list 959.9366 -361.05) 
(list 959.9368 -362.7083) 
(list 959.9369 -364.3667) 
(list 959.9371 -366.025) 
(list 959.9372 -367.6833) 
(list 959.9374 -369.3417) 
(list 959.9375 -371) 
(list 959.9376 -372.6583) 
(list 959.9377 -374.3167) 
(list 959.9378 -375.975) 
(list 959.9379 -377.6333) 
(list 959.938 -379.2917) 
(list 959.9381 -380.95) 
(list 959.9381 -382.6083) 
(list 959.9382 -384.2667) 
(list 959.9383 -385.925) 
(list 959.9383 -387.5833) 
(list 959.9383 -389.2417) 
(list 959.9384 -390.9) 
(list 959.9384 -392.5583) 
(list 959.9384 -394.2167) 
(list 959.9384 -395.875) 
(list 959.9385 -397.5333) 
(list 959.9385 -399.1917) 
(list 959.9385 -400.85) 
(list 959.9385 -402.5083) 
(list 959.9385 -404.1667) 
(list 959.9385 -405.825) 
(list 959.9385 -407.4833) 
(list 959.9385 -409.1417) 
(list 959.9385 -410.8)))
(apply 'command (append '("pline") coords '("c")))
(setq currobj (ssadd (entlast) currobj))
(command "_layer" "set" "prebias" "")
(command "_rectangle" "959.815,-410.8" "960.185,-211.8")
(setq currobj (ssadd (entlast) currobj))
(command "_layer" "set" "nitride" "")
(setq singlenanobeam3 currobj)
(setq currobj nil)
(setq currobj (ssadd))
; DRAWING NODE ARRAY
(setq coords (list 
(list 960.185 -211.8) 
(list 960.5625 -201.8) 
(list 960.5625 -201.8) 
(list 960.5625 -200.8) 
(list 1034.585 -212.6864) 
(list 1034.585 -207.7434) 
(list 960.5625 -197.357) 
(list 960.5625 -196.357) 
(list 960.5625 -196.357) 
(list 960.2625 -186.357) 
(list 959.7375 -186.357) 
(list 959.4375 -196.357) 
(list 959.4375 -196.357) 
(list 959.4375 -197.357) 
(list 885.415 -207.7434) 
(list 885.415 -212.6864) 
(list 959.4375 -200.8) 
(list 959.4375 -201.8) 
(list 959.4375 -201.8) 
(list 959.815 -211.8)))
(apply 'command (append '("pline") coords '("c")))
(setq currobj (ssadd (entlast) currobj))
(command "_layer" "set" "prebias" "")
(setq coords (list 
(list 959.4375 -212.6864) 
(list 959.4375 -200.8) 
(list 885.415 -212.6864) 
(list 885.415 -207.7434) 
(list 959.4375 -197.357) 
(list 959.4375 -186.357) 
(list 960.5625 -186.357) 
(list 960.5625 -197.357) 
(list 1034.585 -207.7434) 
(list 1034.585 -212.6864) 
(list 960.5625 -200.8) 
(list 960.5625 -212.6864)))
(apply 'command (append '("pline") coords '("c")))
(setq currobj (ssadd (entlast) currobj))
(command "_layer" "set" "nitride" "")
(command "_layer" "set" "fda1" "")
(setq coords (list 
(list 960.5625 -200.657) 
(list 1034.585 -212.5434) 
(list 1034.585 -212.3664) 
(list 960.5625 -200.58)))
(apply 'command (append '("pline") coords '("c")))
(setq currobj (ssadd (entlast) currobj))
(setq coords (list 
(list 960.5625 -200.437) 
(list 1034.585 -212.2234) 
(list 1034.585 -212.0464) 
(list 960.5625 -200.36)))
(apply 'command (append '("pline") coords '("c")))
(setq currobj (ssadd (entlast) currobj))
(setq coords (list 
(list 960.5625 -200.217) 
(list 1034.585 -211.9034) 
(list 1034.585 -211.7264) 
(list 960.5625 -200.14)))
(apply 'command (append '("pline") coords '("c")))
(setq currobj (ssadd (entlast) currobj))
(setq coords (list 
(list 960.5625 -199.997) 
(list 1034.585 -211.5834) 
(list 1034.585 -211.4064) 
(list 960.5625 -199.92)))
(apply 'command (append '("pline") coords '("c")))
(setq currobj (ssadd (entlast) currobj))
(setq coords (list 
(list 960.5625 -199.777) 
(list 1034.585 -211.2634) 
(list 1034.585 -211.0864) 
(list 960.5625 -199.7)))
(apply 'command (append '("pline") coords '("c")))
(setq currobj (ssadd (entlast) currobj))
(setq coords (list 
(list 960.5625 -199.557) 
(list 1034.585 -210.9434) 
(list 1034.585 -210.7664) 
(list 960.5625 -199.48)))
(apply 'command (append '("pline") coords '("c")))
(setq currobj (ssadd (entlast) currobj))
(setq coords (list 
(list 960.5625 -199.337) 
(list 1034.585 -210.6234) 
(list 1034.585 -210.4464) 
(list 960.5625 -199.26)))
(apply 'command (append '("pline") coords '("c")))
(setq currobj (ssadd (entlast) currobj))
(setq coords (list 
(list 960.5625 -199.117) 
(list 1034.585 -210.3034) 
(list 1034.585 -210.1264) 
(list 960.5625 -199.04)))
(apply 'command (append '("pline") coords '("c")))
(setq currobj (ssadd (entlast) currobj))
(setq coords (list 
(list 960.5625 -198.897) 
(list 1034.585 -209.9834) 
(list 1034.585 -209.8064) 
(list 960.5625 -198.82)))
(apply 'command (append '("pline") coords '("c")))
(setq currobj (ssadd (entlast) currobj))
(setq coords (list 
(list 960.5625 -198.677) 
(list 1034.585 -209.6634) 
(list 1034.585 -209.4864) 
(list 960.5625 -198.6)))
(apply 'command (append '("pline") coords '("c")))
(setq currobj (ssadd (entlast) currobj))
(setq coords (list 
(list 960.5625 -198.457) 
(list 1034.585 -209.3434) 
(list 1034.585 -209.1664) 
(list 960.5625 -198.38)))
(apply 'command (append '("pline") coords '("c")))
(setq currobj (ssadd (entlast) currobj))
(setq coords (list 
(list 960.5625 -198.237) 
(list 1034.585 -209.0234) 
(list 1034.585 -208.8464) 
(list 960.5625 -198.16)))
(apply 'command (append '("pline") coords '("c")))
(setq currobj (ssadd (entlast) currobj))
(setq coords (list 
(list 960.5625 -198.017) 
(list 1034.585 -208.7034) 
(list 1034.585 -208.5264) 
(list 960.5625 -197.94)))
(apply 'command (append '("pline") coords '("c")))
(setq currobj (ssadd (entlast) currobj))
(setq coords (list 
(list 960.5625 -197.797) 
(list 1034.585 -208.3834) 
(list 1034.585 -208.2064) 
(list 960.5625 -197.72)))
(apply 'command (append '("pline") coords '("c")))
(setq currobj (ssadd (entlast) currobj))
(setq coords (list 
(list 960.5625 -197.577) 
(list 1034.585 -208.0634) 
(list 1034.585 -207.8864) 
(list 960.5625 -197.5)))
(apply 'command (append '("pline") coords '("c")))
(setq currobj (ssadd (entlast) currobj))
(setq coords (list 
(list 959.4375 -197.5) 
(list 885.415 -207.8864) 
(list 885.415 -208.0634) 
(list 959.4375 -197.577)))
(apply 'command (append '("pline") coords '("c")))
(setq currobj (ssadd (entlast) currobj))
(setq coords (list 
(list 959.4375 -197.72) 
(list 885.415 -208.2064) 
(list 885.415 -208.3834) 
(list 959.4375 -197.797)))
(apply 'command (append '("pline") coords '("c")))
(setq currobj (ssadd (entlast) currobj))
(setq coords (list 
(list 959.4375 -197.94) 
(list 885.415 -208.5264) 
(list 885.415 -208.7034) 
(list 959.4375 -198.017)))
(apply 'command (append '("pline") coords '("c")))
(setq currobj (ssadd (entlast) currobj))
(setq coords (list 
(list 959.4375 -198.16) 
(list 885.415 -208.8464) 
(list 885.415 -209.0234) 
(list 959.4375 -198.237)))
(apply 'command (append '("pline") coords '("c")))
(setq currobj (ssadd (entlast) currobj))
(setq coords (list 
(list 959.4375 -198.38) 
(list 885.415 -209.1664) 
(list 885.415 -209.3434) 
(list 959.4375 -198.457)))
(apply 'command (append '("pline") coords '("c")))
(setq currobj (ssadd (entlast) currobj))
(setq coords (list 
(list 959.4375 -198.6) 
(list 885.415 -209.4864) 
(list 885.415 -209.6634) 
(list 959.4375 -198.677)))
(apply 'command (append '("pline") coords '("c")))
(setq currobj (ssadd (entlast) currobj))
(setq coords (list 
(list 959.4375 -198.82) 
(list 885.415 -209.8064) 
(list 885.415 -209.9834) 
(list 959.4375 -198.897)))
(apply 'command (append '("pline") coords '("c")))
(setq currobj (ssadd (entlast) currobj))
(setq coords (list 
(list 959.4375 -199.04) 
(list 885.415 -210.1264) 
(list 885.415 -210.3034) 
(list 959.4375 -199.117)))
(apply 'command (append '("pline") coords '("c")))
(setq currobj (ssadd (entlast) currobj))
(setq coords (list 
(list 959.4375 -199.26) 
(list 885.415 -210.4464) 
(list 885.415 -210.6234) 
(list 959.4375 -199.337)))
(apply 'command (append '("pline") coords '("c")))
(setq currobj (ssadd (entlast) currobj))
(setq coords (list 
(list 959.4375 -199.48) 
(list 885.415 -210.7664) 
(list 885.415 -210.9434) 
(list 959.4375 -199.557)))
(apply 'command (append '("pline") coords '("c")))
(setq currobj (ssadd (entlast) currobj))
(setq coords (list 
(list 959.4375 -199.7) 
(list 885.415 -211.0864) 
(list 885.415 -211.2634) 
(list 959.4375 -199.777)))
(apply 'command (append '("pline") coords '("c")))
(setq currobj (ssadd (entlast) currobj))
(setq coords (list 
(list 959.4375 -199.92) 
(list 885.415 -211.4064) 
(list 885.415 -211.5834) 
(list 959.4375 -199.997)))
(apply 'command (append '("pline") coords '("c")))
(setq currobj (ssadd (entlast) currobj))
(setq coords (list 
(list 959.4375 -200.14) 
(list 885.415 -211.7264) 
(list 885.415 -211.9034) 
(list 959.4375 -200.217)))
(apply 'command (append '("pline") coords '("c")))
(setq currobj (ssadd (entlast) currobj))
(setq coords (list 
(list 959.4375 -200.36) 
(list 885.415 -212.0464) 
(list 885.415 -212.2234) 
(list 959.4375 -200.437)))
(apply 'command (append '("pline") coords '("c")))
(setq currobj (ssadd (entlast) currobj))
(setq coords (list 
(list 959.4375 -200.58) 
(list 885.415 -212.3664) 
(list 885.415 -212.5434) 
(list 959.4375 -200.657)))
(apply 'command (append '("pline") coords '("c")))
(setq currobj (ssadd (entlast) currobj))
(command "_layer" "set" "nitride" "")
(command "_layer" "set" "text" "")
(command "_circle" "958.985,-211.8" "0.075")
(command "_circle" "958.985,-211.5" "0.075")
(command "_circle" "958.985,-211.2" "0.075")
(command "_circle" "958.985,-210.9" "0.075")
(command "_circle" "958.985,-210.6" "0.075")
(command "_circle" "958.685,-211.8" "0.075")
(command "_circle" "958.685,-211.5" "0.075")
(command "_circle" "958.685,-211.2" "0.075")
(command "_circle" "958.685,-210.9" "0.075")
(command "_circle" "958.685,-210.6" "0.075")
(command "_circle" "958.385,-211.8" "0.075")
(command "_circle" "958.385,-211.5" "0.075")
(command "_circle" "958.385,-211.2" "0.075")
(command "_circle" "958.385,-210.9" "0.075")
(command "_circle" "958.385,-210.6" "0.075")
(command "_circle" "958.085,-211.8" "0.075")
(command "_circle" "958.085,-211.5" "0.075")
(command "_circle" "958.085,-211.2" "0.075")
(command "_circle" "958.085,-210.9" "0.075")
(command "_circle" "958.085,-210.6" "0.075")
(command "_circle" "957.785,-211.8" "0.075")
(command "_circle" "957.785,-211.5" "0.075")
(command "_circle" "957.785,-211.2" "0.075")
(command "_circle" "957.785,-210.9" "0.075")
(command "_circle" "957.785,-210.6" "0.075")
(command "_layer" "set" "nitride" "")
(setq anglednodearray3 currobj)
(setq currobj nil)
(setq currobj (ssadd))
; DRAWING COOLED SINGLE NANOBEAM
(setq coords (list 
(list 960.2625 -186.357) 
(list 960.2625 -181.357) 
(list 959.7375 -181.357) 
(list 959.7375 -186.357)))
(apply 'command (append '("pline") coords '("c")))
(setq currobj (ssadd (entlast) currobj))
(command "_layer" "set" "prebias" "")
(command "_rectangle" "959.7375,-186.357" "960.2625,-181.357")
(setq currobj (ssadd (entlast) currobj))
(command "_layer" "set" "nitride" "")
(setq coords (list 
(list 960.2625 -181.357) 
(list 960.5625 -171.357) 
(list 960.5625 -171.357) 
(list 960.5625 -170.357) 
(list 1034.585 -171.107) 
(list 1034.585 -166.164) 
(list 960.5625 -166.914) 
(list 960.5625 -165.914) 
(list 960.5625 -165.914) 
(list 960.2625 -155.914) 
(list 959.7375 -155.914) 
(list 959.4375 -165.914) 
(list 959.4375 -165.914) 
(list 959.4375 -166.914) 
(list 885.415 -166.164) 
(list 885.415 -171.107) 
(list 959.4375 -170.357) 
(list 959.4375 -171.357) 
(list 959.4375 -171.357) 
(list 959.7375 -181.357)))
(apply 'command (append '("pline") coords '("c")))
(setq currobj (ssadd (entlast) currobj))
(command "_layer" "set" "prebias" "")
(setq coords (list 
(list 959.4375 -181.357) 
(list 959.4375 -170.357) 
(list 885.415 -171.107) 
(list 885.415 -166.164) 
(list 959.4375 -166.914) 
(list 959.4375 -155.914) 
(list 960.5625 -155.914) 
(list 960.5625 -166.914) 
(list 1034.585 -166.164) 
(list 1034.585 -171.107) 
(list 960.5625 -170.357) 
(list 960.5625 -181.357)))
(apply 'command (append '("pline") coords '("c")))
(setq currobj (ssadd (entlast) currobj))
(command "_layer" "set" "nitride" "")
(command "_layer" "set" "fda1" "")
(setq coords (list 
(list 960.5625 -170.214) 
(list 1034.585 -170.964) 
(list 1034.585 -170.787) 
(list 960.5625 -170.137)))
(apply 'command (append '("pline") coords '("c")))
(setq currobj (ssadd (entlast) currobj))
(setq coords (list 
(list 960.5625 -169.994) 
(list 1034.585 -170.644) 
(list 1034.585 -170.467) 
(list 960.5625 -169.917)))
(apply 'command (append '("pline") coords '("c")))
(setq currobj (ssadd (entlast) currobj))
(setq coords (list 
(list 960.5625 -169.774) 
(list 1034.585 -170.324) 
(list 1034.585 -170.147) 
(list 960.5625 -169.697)))
(apply 'command (append '("pline") coords '("c")))
(setq currobj (ssadd (entlast) currobj))
(setq coords (list 
(list 960.5625 -169.554) 
(list 1034.585 -170.004) 
(list 1034.585 -169.827) 
(list 960.5625 -169.477)))
(apply 'command (append '("pline") coords '("c")))
(setq currobj (ssadd (entlast) currobj))
(setq coords (list 
(list 960.5625 -169.334) 
(list 1034.585 -169.684) 
(list 1034.585 -169.507) 
(list 960.5625 -169.257)))
(apply 'command (append '("pline") coords '("c")))
(setq currobj (ssadd (entlast) currobj))
(setq coords (list 
(list 960.5625 -169.114) 
(list 1034.585 -169.364) 
(list 1034.585 -169.187) 
(list 960.5625 -169.037)))
(apply 'command (append '("pline") coords '("c")))
(setq currobj (ssadd (entlast) currobj))
(setq coords (list 
(list 960.5625 -168.894) 
(list 1034.585 -169.044) 
(list 1034.585 -168.867) 
(list 960.5625 -168.817)))
(apply 'command (append '("pline") coords '("c")))
(setq currobj (ssadd (entlast) currobj))
(setq coords (list 
(list 960.5625 -168.674) 
(list 1034.585 -168.724) 
(list 1034.585 -168.547) 
(list 960.5625 -168.597)))
(apply 'command (append '("pline") coords '("c")))
(setq currobj (ssadd (entlast) currobj))
(setq coords (list 
(list 960.5625 -168.454) 
(list 1034.585 -168.404) 
(list 1034.585 -168.227) 
(list 960.5625 -168.377)))
(apply 'command (append '("pline") coords '("c")))
(setq currobj (ssadd (entlast) currobj))
(setq coords (list 
(list 960.5625 -168.234) 
(list 1034.585 -168.084) 
(list 1034.585 -167.907) 
(list 960.5625 -168.157)))
(apply 'command (append '("pline") coords '("c")))
(setq currobj (ssadd (entlast) currobj))
(setq coords (list 
(list 960.5625 -168.014) 
(list 1034.585 -167.764) 
(list 1034.585 -167.587) 
(list 960.5625 -167.937)))
(apply 'command (append '("pline") coords '("c")))
(setq currobj (ssadd (entlast) currobj))
(setq coords (list 
(list 960.5625 -167.794) 
(list 1034.585 -167.444) 
(list 1034.585 -167.267) 
(list 960.5625 -167.717)))
(apply 'command (append '("pline") coords '("c")))
(setq currobj (ssadd (entlast) currobj))
(setq coords (list 
(list 960.5625 -167.574) 
(list 1034.585 -167.124) 
(list 1034.585 -166.947) 
(list 960.5625 -167.497)))
(apply 'command (append '("pline") coords '("c")))
(setq currobj (ssadd (entlast) currobj))
(setq coords (list 
(list 960.5625 -167.354) 
(list 1034.585 -166.804) 
(list 1034.585 -166.627) 
(list 960.5625 -167.277)))
(apply 'command (append '("pline") coords '("c")))
(setq currobj (ssadd (entlast) currobj))
(setq coords (list 
(list 960.5625 -167.134) 
(list 1034.585 -166.484) 
(list 1034.585 -166.307) 
(list 960.5625 -167.057)))
(apply 'command (append '("pline") coords '("c")))
(setq currobj (ssadd (entlast) currobj))
(setq coords (list 
(list 959.4375 -167.057) 
(list 885.415 -166.307) 
(list 885.415 -166.484) 
(list 959.4375 -167.134)))
(apply 'command (append '("pline") coords '("c")))
(setq currobj (ssadd (entlast) currobj))
(setq coords (list 
(list 959.4375 -167.277) 
(list 885.415 -166.627) 
(list 885.415 -166.804) 
(list 959.4375 -167.354)))
(apply 'command (append '("pline") coords '("c")))
(setq currobj (ssadd (entlast) currobj))
(setq coords (list 
(list 959.4375 -167.497) 
(list 885.415 -166.947) 
(list 885.415 -167.124) 
(list 959.4375 -167.574)))
(apply 'command (append '("pline") coords '("c")))
(setq currobj (ssadd (entlast) currobj))
(setq coords (list 
(list 959.4375 -167.717) 
(list 885.415 -167.267) 
(list 885.415 -167.444) 
(list 959.4375 -167.794)))
(apply 'command (append '("pline") coords '("c")))
(setq currobj (ssadd (entlast) currobj))
(setq coords (list 
(list 959.4375 -167.937) 
(list 885.415 -167.587) 
(list 885.415 -167.764) 
(list 959.4375 -168.014)))
(apply 'command (append '("pline") coords '("c")))
(setq currobj (ssadd (entlast) currobj))
(setq coords (list 
(list 959.4375 -168.157) 
(list 885.415 -167.907) 
(list 885.415 -168.084) 
(list 959.4375 -168.234)))
(apply 'command (append '("pline") coords '("c")))
(setq currobj (ssadd (entlast) currobj))
(setq coords (list 
(list 959.4375 -168.377) 
(list 885.415 -168.227) 
(list 885.415 -168.404) 
(list 959.4375 -168.454)))
(apply 'command (append '("pline") coords '("c")))
(setq currobj (ssadd (entlast) currobj))
(setq coords (list 
(list 959.4375 -168.597) 
(list 885.415 -168.547) 
(list 885.415 -168.724) 
(list 959.4375 -168.674)))
(apply 'command (append '("pline") coords '("c")))
(setq currobj (ssadd (entlast) currobj))
(setq coords (list 
(list 959.4375 -168.817) 
(list 885.415 -168.867) 
(list 885.415 -169.044) 
(list 959.4375 -168.894)))
(apply 'command (append '("pline") coords '("c")))
(setq currobj (ssadd (entlast) currobj))
(setq coords (list 
(list 959.4375 -169.037) 
(list 885.415 -169.187) 
(list 885.415 -169.364) 
(list 959.4375 -169.114)))
(apply 'command (append '("pline") coords '("c")))
(setq currobj (ssadd (entlast) currobj))
(setq coords (list 
(list 959.4375 -169.257) 
(list 885.415 -169.507) 
(list 885.415 -169.684) 
(list 959.4375 -169.334)))
(apply 'command (append '("pline") coords '("c")))
(setq currobj (ssadd (entlast) currobj))
(setq coords (list 
(list 959.4375 -169.477) 
(list 885.415 -169.827) 
(list 885.415 -170.004) 
(list 959.4375 -169.554)))
(apply 'command (append '("pline") coords '("c")))
(setq currobj (ssadd (entlast) currobj))
(setq coords (list 
(list 959.4375 -169.697) 
(list 885.415 -170.147) 
(list 885.415 -170.324) 
(list 959.4375 -169.774)))
(apply 'command (append '("pline") coords '("c")))
(setq currobj (ssadd (entlast) currobj))
(setq coords (list 
(list 959.4375 -169.917) 
(list 885.415 -170.467) 
(list 885.415 -170.644) 
(list 959.4375 -169.994)))
(apply 'command (append '("pline") coords '("c")))
(setq currobj (ssadd (entlast) currobj))
(setq coords (list 
(list 959.4375 -170.137) 
(list 885.415 -170.787) 
(list 885.415 -170.964) 
(list 959.4375 -170.214)))
(apply 'command (append '("pline") coords '("c")))
(setq currobj (ssadd (entlast) currobj))
(command "_layer" "set" "nitride" "")
(command "_layer" "set" "text" "")
(command "_circle" "959.0625,-181.357" "0.075")
(command "_circle" "959.0625,-181.057" "0.075")
(command "_circle" "959.0625,-180.757" "0.075")
(command "_circle" "959.0625,-180.457" "0.075")
(command "_circle" "959.0625,-180.157" "0.075")
(command "_circle" "958.7625,-181.357" "0.075")
(command "_circle" "958.7625,-181.057" "0.075")
(command "_circle" "958.7625,-180.757" "0.075")
(command "_circle" "958.7625,-180.457" "0.075")
(command "_circle" "958.7625,-180.157" "0.075")
(command "_circle" "958.4625,-181.357" "0.075")
(command "_circle" "958.4625,-181.057" "0.075")
(command "_circle" "958.4625,-180.757" "0.075")
(command "_circle" "958.4625,-180.457" "0.075")
(command "_circle" "958.4625,-180.157" "0.075")
(command "_circle" "958.1625,-181.357" "0.075")
(command "_circle" "958.1625,-181.057" "0.075")
(command "_circle" "958.1625,-180.757" "0.075")
(command "_circle" "958.1625,-180.457" "0.075")
(command "_circle" "958.1625,-180.157" "0.075")
(command "_circle" "957.8625,-181.357" "0.075")
(command "_circle" "957.8625,-181.057" "0.075")
(command "_circle" "957.8625,-180.757" "0.075")
(command "_circle" "957.8625,-180.457" "0.075")
(command "_circle" "957.8625,-180.157" "0.075")
(command "_layer" "set" "nitride" "")
(setq coords (list 
(list 960.2625 -155.914) 
(list 960.2625 -40.2693) 
(list 959.7375 -40.2693) 
(list 959.7375 -155.914)))
(apply 'command (append '("pline") coords '("c")))
(setq currobj (ssadd (entlast) currobj))
(command "_layer" "set" "prebias" "")
(command "_rectangle" "959.7375,-155.914" "960.2625,-40.2693")
(setq currobj (ssadd (entlast) currobj))
(command "_layer" "set" "nitride" "")
(setq coords (list 
(list 960.2625 -40.2693) 
(list 960.5625 -30.2693) 
(list 960.5625 -30.2693) 
(list 960.5625 -29.2693) 
(list 1034.585 -30.0193) 
(list 1034.585 -25.0763) 
(list 960.5625 -25.8263) 
(list 960.5625 -24.8263) 
(list 960.5625 -24.8263) 
(list 960.2625 -14.8263) 
(list 959.7375 -14.8263) 
(list 959.4375 -24.8263) 
(list 959.4375 -24.8263) 
(list 959.4375 -25.8263) 
(list 885.415 -25.0763) 
(list 885.415 -30.0193) 
(list 959.4375 -29.2693) 
(list 959.4375 -30.2693) 
(list 959.4375 -30.2693) 
(list 959.7375 -40.2693)))
(apply 'command (append '("pline") coords '("c")))
(setq currobj (ssadd (entlast) currobj))
(command "_layer" "set" "prebias" "")
(setq coords (list 
(list 959.4375 -40.2693) 
(list 959.4375 -29.2693) 
(list 885.415 -30.0193) 
(list 885.415 -25.0763) 
(list 959.4375 -25.8263) 
(list 959.4375 -14.8263) 
(list 960.5625 -14.8263) 
(list 960.5625 -25.8263) 
(list 1034.585 -25.0763) 
(list 1034.585 -30.0193) 
(list 960.5625 -29.2693) 
(list 960.5625 -40.2693)))
(apply 'command (append '("pline") coords '("c")))
(setq currobj (ssadd (entlast) currobj))
(command "_layer" "set" "nitride" "")
(command "_layer" "set" "fda1" "")
(setq coords (list 
(list 960.5625 -29.1263) 
(list 1034.585 -29.8763) 
(list 1034.585 -29.6993) 
(list 960.5625 -29.0493)))
(apply 'command (append '("pline") coords '("c")))
(setq currobj (ssadd (entlast) currobj))
(setq coords (list 
(list 960.5625 -28.9063) 
(list 1034.585 -29.5563) 
(list 1034.585 -29.3793) 
(list 960.5625 -28.8293)))
(apply 'command (append '("pline") coords '("c")))
(setq currobj (ssadd (entlast) currobj))
(setq coords (list 
(list 960.5625 -28.6863) 
(list 1034.585 -29.2363) 
(list 1034.585 -29.0593) 
(list 960.5625 -28.6093)))
(apply 'command (append '("pline") coords '("c")))
(setq currobj (ssadd (entlast) currobj))
(setq coords (list 
(list 960.5625 -28.4663) 
(list 1034.585 -28.9163) 
(list 1034.585 -28.7393) 
(list 960.5625 -28.3893)))
(apply 'command (append '("pline") coords '("c")))
(setq currobj (ssadd (entlast) currobj))
(setq coords (list 
(list 960.5625 -28.2463) 
(list 1034.585 -28.5963) 
(list 1034.585 -28.4193) 
(list 960.5625 -28.1693)))
(apply 'command (append '("pline") coords '("c")))
(setq currobj (ssadd (entlast) currobj))
(setq coords (list 
(list 960.5625 -28.0263) 
(list 1034.585 -28.2763) 
(list 1034.585 -28.0993) 
(list 960.5625 -27.9493)))
(apply 'command (append '("pline") coords '("c")))
(setq currobj (ssadd (entlast) currobj))
(setq coords (list 
(list 960.5625 -27.8063) 
(list 1034.585 -27.9563) 
(list 1034.585 -27.7793) 
(list 960.5625 -27.7293)))
(apply 'command (append '("pline") coords '("c")))
(setq currobj (ssadd (entlast) currobj))
(setq coords (list 
(list 960.5625 -27.5863) 
(list 1034.585 -27.6363) 
(list 1034.585 -27.4593) 
(list 960.5625 -27.5093)))
(apply 'command (append '("pline") coords '("c")))
(setq currobj (ssadd (entlast) currobj))
(setq coords (list 
(list 960.5625 -27.3663) 
(list 1034.585 -27.3163) 
(list 1034.585 -27.1393) 
(list 960.5625 -27.2893)))
(apply 'command (append '("pline") coords '("c")))
(setq currobj (ssadd (entlast) currobj))
(setq coords (list 
(list 960.5625 -27.1463) 
(list 1034.585 -26.9963) 
(list 1034.585 -26.8193) 
(list 960.5625 -27.0693)))
(apply 'command (append '("pline") coords '("c")))
(setq currobj (ssadd (entlast) currobj))
(setq coords (list 
(list 960.5625 -26.9263) 
(list 1034.585 -26.6763) 
(list 1034.585 -26.4993) 
(list 960.5625 -26.8493)))
(apply 'command (append '("pline") coords '("c")))
(setq currobj (ssadd (entlast) currobj))
(setq coords (list 
(list 960.5625 -26.7063) 
(list 1034.585 -26.3563) 
(list 1034.585 -26.1793) 
(list 960.5625 -26.6293)))
(apply 'command (append '("pline") coords '("c")))
(setq currobj (ssadd (entlast) currobj))
(setq coords (list 
(list 960.5625 -26.4863) 
(list 1034.585 -26.0363) 
(list 1034.585 -25.8593) 
(list 960.5625 -26.4093)))
(apply 'command (append '("pline") coords '("c")))
(setq currobj (ssadd (entlast) currobj))
(setq coords (list 
(list 960.5625 -26.2663) 
(list 1034.585 -25.7163) 
(list 1034.585 -25.5393) 
(list 960.5625 -26.1893)))
(apply 'command (append '("pline") coords '("c")))
(setq currobj (ssadd (entlast) currobj))
(setq coords (list 
(list 960.5625 -26.0463) 
(list 1034.585 -25.3963) 
(list 1034.585 -25.2193) 
(list 960.5625 -25.9693)))
(apply 'command (append '("pline") coords '("c")))
(setq currobj (ssadd (entlast) currobj))
(setq coords (list 
(list 959.4375 -25.9693) 
(list 885.415 -25.2193) 
(list 885.415 -25.3963) 
(list 959.4375 -26.0463)))
(apply 'command (append '("pline") coords '("c")))
(setq currobj (ssadd (entlast) currobj))
(setq coords (list 
(list 959.4375 -26.1893) 
(list 885.415 -25.5393) 
(list 885.415 -25.7163) 
(list 959.4375 -26.2663)))
(apply 'command (append '("pline") coords '("c")))
(setq currobj (ssadd (entlast) currobj))
(setq coords (list 
(list 959.4375 -26.4093) 
(list 885.415 -25.8593) 
(list 885.415 -26.0363) 
(list 959.4375 -26.4863)))
(apply 'command (append '("pline") coords '("c")))
(setq currobj (ssadd (entlast) currobj))
(setq coords (list 
(list 959.4375 -26.6293) 
(list 885.415 -26.1793) 
(list 885.415 -26.3563) 
(list 959.4375 -26.7063)))
(apply 'command (append '("pline") coords '("c")))
(setq currobj (ssadd (entlast) currobj))
(setq coords (list 
(list 959.4375 -26.8493) 
(list 885.415 -26.4993) 
(list 885.415 -26.6763) 
(list 959.4375 -26.9263)))
(apply 'command (append '("pline") coords '("c")))
(setq currobj (ssadd (entlast) currobj))
(setq coords (list 
(list 959.4375 -27.0693) 
(list 885.415 -26.8193) 
(list 885.415 -26.9963) 
(list 959.4375 -27.1463)))
(apply 'command (append '("pline") coords '("c")))
(setq currobj (ssadd (entlast) currobj))
(setq coords (list 
(list 959.4375 -27.2893) 
(list 885.415 -27.1393) 
(list 885.415 -27.3163) 
(list 959.4375 -27.3663)))
(apply 'command (append '("pline") coords '("c")))
(setq currobj (ssadd (entlast) currobj))
(setq coords (list 
(list 959.4375 -27.5093) 
(list 885.415 -27.4593) 
(list 885.415 -27.6363) 
(list 959.4375 -27.5863)))
(apply 'command (append '("pline") coords '("c")))
(setq currobj (ssadd (entlast) currobj))
(setq coords (list 
(list 959.4375 -27.7293) 
(list 885.415 -27.7793) 
(list 885.415 -27.9563) 
(list 959.4375 -27.8063)))
(apply 'command (append '("pline") coords '("c")))
(setq currobj (ssadd (entlast) currobj))
(setq coords (list 
(list 959.4375 -27.9493) 
(list 885.415 -28.0993) 
(list 885.415 -28.2763) 
(list 959.4375 -28.0263)))
(apply 'command (append '("pline") coords '("c")))
(setq currobj (ssadd (entlast) currobj))
(setq coords (list 
(list 959.4375 -28.1693) 
(list 885.415 -28.4193) 
(list 885.415 -28.5963) 
(list 959.4375 -28.2463)))
(apply 'command (append '("pline") coords '("c")))
(setq currobj (ssadd (entlast) currobj))
(setq coords (list 
(list 959.4375 -28.3893) 
(list 885.415 -28.7393) 
(list 885.415 -28.9163) 
(list 959.4375 -28.4663)))
(apply 'command (append '("pline") coords '("c")))
(setq currobj (ssadd (entlast) currobj))
(setq coords (list 
(list 959.4375 -28.6093) 
(list 885.415 -29.0593) 
(list 885.415 -29.2363) 
(list 959.4375 -28.6863)))
(apply 'command (append '("pline") coords '("c")))
(setq currobj (ssadd (entlast) currobj))
(setq coords (list 
(list 959.4375 -28.8293) 
(list 885.415 -29.3793) 
(list 885.415 -29.5563) 
(list 959.4375 -28.9063)))
(apply 'command (append '("pline") coords '("c")))
(setq currobj (ssadd (entlast) currobj))
(setq coords (list 
(list 959.4375 -29.0493) 
(list 885.415 -29.6993) 
(list 885.415 -29.8763) 
(list 959.4375 -29.1263)))
(apply 'command (append '("pline") coords '("c")))
(setq currobj (ssadd (entlast) currobj))
(command "_layer" "set" "nitride" "")
(command "_layer" "set" "text" "")
(command "_circle" "959.0625,-40.2693" "0.075")
(command "_circle" "959.0625,-39.9693" "0.075")
(command "_circle" "959.0625,-39.6693" "0.075")
(command "_circle" "959.0625,-39.3693" "0.075")
(command "_circle" "959.0625,-39.0693" "0.075")
(command "_circle" "958.7625,-40.2693" "0.075")
(command "_circle" "958.7625,-39.9693" "0.075")
(command "_circle" "958.7625,-39.6693" "0.075")
(command "_circle" "958.7625,-39.3693" "0.075")
(command "_circle" "958.7625,-39.0693" "0.075")
(command "_circle" "958.4625,-40.2693" "0.075")
(command "_circle" "958.4625,-39.9693" "0.075")
(command "_circle" "958.4625,-39.6693" "0.075")
(command "_circle" "958.4625,-39.3693" "0.075")
(command "_circle" "958.4625,-39.0693" "0.075")
(command "_circle" "958.1625,-40.2693" "0.075")
(command "_circle" "958.1625,-39.9693" "0.075")
(command "_circle" "958.1625,-39.6693" "0.075")
(command "_circle" "958.1625,-39.3693" "0.075")
(command "_circle" "958.1625,-39.0693" "0.075")
(command "_circle" "957.8625,-40.2693" "0.075")
(command "_circle" "957.8625,-39.9693" "0.075")
(command "_circle" "957.8625,-39.6693" "0.075")
(command "_circle" "957.8625,-39.3693" "0.075")
(command "_circle" "957.8625,-39.0693" "0.075")
(command "_layer" "set" "nitride" "")
(setq coords (list 
(list 960.2625 -14.8263) 
(list 960.2625 100.8184) 
(list 959.7375 100.8184) 
(list 959.7375 -14.8263)))
(apply 'command (append '("pline") coords '("c")))
(setq currobj (ssadd (entlast) currobj))
(command "_layer" "set" "prebias" "")
(command "_rectangle" "959.7375,-14.8263" "960.2625,100.8184")
(setq currobj (ssadd (entlast) currobj))
(command "_layer" "set" "nitride" "")
(setq coords (list 
(list 960.2625 100.8184) 
(list 960.5625 110.8184) 
(list 960.5625 110.8184) 
(list 960.5625 111.8184) 
(list 1034.585 111.0684) 
(list 1034.585 116.0114) 
(list 960.5625 115.2614) 
(list 960.5625 116.2614) 
(list 960.5625 116.2614) 
(list 960.2625 126.2614) 
(list 959.7375 126.2614) 
(list 959.4375 116.2614) 
(list 959.4375 116.2614) 
(list 959.4375 115.2614) 
(list 885.415 116.0114) 
(list 885.415 111.0684) 
(list 959.4375 111.8184) 
(list 959.4375 110.8184) 
(list 959.4375 110.8184) 
(list 959.7375 100.8184)))
(apply 'command (append '("pline") coords '("c")))
(setq currobj (ssadd (entlast) currobj))
(command "_layer" "set" "prebias" "")
(setq coords (list 
(list 959.4375 100.8184) 
(list 959.4375 111.8184) 
(list 885.415 111.0684) 
(list 885.415 116.0114) 
(list 959.4375 115.2614) 
(list 959.4375 126.2614) 
(list 960.5625 126.2614) 
(list 960.5625 115.2614) 
(list 1034.585 116.0114) 
(list 1034.585 111.0684) 
(list 960.5625 111.8184) 
(list 960.5625 100.8184)))
(apply 'command (append '("pline") coords '("c")))
(setq currobj (ssadd (entlast) currobj))
(command "_layer" "set" "nitride" "")
(command "_layer" "set" "fda1" "")
(setq coords (list 
(list 960.5625 111.9614) 
(list 1034.585 111.2114) 
(list 1034.585 111.3884) 
(list 960.5625 112.0384)))
(apply 'command (append '("pline") coords '("c")))
(setq currobj (ssadd (entlast) currobj))
(setq coords (list 
(list 960.5625 112.1814) 
(list 1034.585 111.5314) 
(list 1034.585 111.7084) 
(list 960.5625 112.2584)))
(apply 'command (append '("pline") coords '("c")))
(setq currobj (ssadd (entlast) currobj))
(setq coords (list 
(list 960.5625 112.4014) 
(list 1034.585 111.8514) 
(list 1034.585 112.0284) 
(list 960.5625 112.4784)))
(apply 'command (append '("pline") coords '("c")))
(setq currobj (ssadd (entlast) currobj))
(setq coords (list 
(list 960.5625 112.6214) 
(list 1034.585 112.1714) 
(list 1034.585 112.3484) 
(list 960.5625 112.6984)))
(apply 'command (append '("pline") coords '("c")))
(setq currobj (ssadd (entlast) currobj))
(setq coords (list 
(list 960.5625 112.8414) 
(list 1034.585 112.4914) 
(list 1034.585 112.6684) 
(list 960.5625 112.9184)))
(apply 'command (append '("pline") coords '("c")))
(setq currobj (ssadd (entlast) currobj))
(setq coords (list 
(list 960.5625 113.0614) 
(list 1034.585 112.8114) 
(list 1034.585 112.9884) 
(list 960.5625 113.1384)))
(apply 'command (append '("pline") coords '("c")))
(setq currobj (ssadd (entlast) currobj))
(setq coords (list 
(list 960.5625 113.2814) 
(list 1034.585 113.1314) 
(list 1034.585 113.3084) 
(list 960.5625 113.3584)))
(apply 'command (append '("pline") coords '("c")))
(setq currobj (ssadd (entlast) currobj))
(setq coords (list 
(list 960.5625 113.5014) 
(list 1034.585 113.4514) 
(list 1034.585 113.6284) 
(list 960.5625 113.5784)))
(apply 'command (append '("pline") coords '("c")))
(setq currobj (ssadd (entlast) currobj))
(setq coords (list 
(list 960.5625 113.7214) 
(list 1034.585 113.7714) 
(list 1034.585 113.9484) 
(list 960.5625 113.7984)))
(apply 'command (append '("pline") coords '("c")))
(setq currobj (ssadd (entlast) currobj))
(setq coords (list 
(list 960.5625 113.9414) 
(list 1034.585 114.0914) 
(list 1034.585 114.2684) 
(list 960.5625 114.0184)))
(apply 'command (append '("pline") coords '("c")))
(setq currobj (ssadd (entlast) currobj))
(setq coords (list 
(list 960.5625 114.1614) 
(list 1034.585 114.4114) 
(list 1034.585 114.5884) 
(list 960.5625 114.2384)))
(apply 'command (append '("pline") coords '("c")))
(setq currobj (ssadd (entlast) currobj))
(setq coords (list 
(list 960.5625 114.3814) 
(list 1034.585 114.7314) 
(list 1034.585 114.9084) 
(list 960.5625 114.4584)))
(apply 'command (append '("pline") coords '("c")))
(setq currobj (ssadd (entlast) currobj))
(setq coords (list 
(list 960.5625 114.6014) 
(list 1034.585 115.0514) 
(list 1034.585 115.2284) 
(list 960.5625 114.6784)))
(apply 'command (append '("pline") coords '("c")))
(setq currobj (ssadd (entlast) currobj))
(setq coords (list 
(list 960.5625 114.8214) 
(list 1034.585 115.3714) 
(list 1034.585 115.5484) 
(list 960.5625 114.8984)))
(apply 'command (append '("pline") coords '("c")))
(setq currobj (ssadd (entlast) currobj))
(setq coords (list 
(list 960.5625 115.0414) 
(list 1034.585 115.6914) 
(list 1034.585 115.8684) 
(list 960.5625 115.1184)))
(apply 'command (append '("pline") coords '("c")))
(setq currobj (ssadd (entlast) currobj))
(setq coords (list 
(list 959.4375 115.1184) 
(list 885.415 115.8684) 
(list 885.415 115.6914) 
(list 959.4375 115.0414)))
(apply 'command (append '("pline") coords '("c")))
(setq currobj (ssadd (entlast) currobj))
(setq coords (list 
(list 959.4375 114.8984) 
(list 885.415 115.5484) 
(list 885.415 115.3714) 
(list 959.4375 114.8214)))
(apply 'command (append '("pline") coords '("c")))
(setq currobj (ssadd (entlast) currobj))
(setq coords (list 
(list 959.4375 114.6784) 
(list 885.415 115.2284) 
(list 885.415 115.0514) 
(list 959.4375 114.6014)))
(apply 'command (append '("pline") coords '("c")))
(setq currobj (ssadd (entlast) currobj))
(setq coords (list 
(list 959.4375 114.4584) 
(list 885.415 114.9084) 
(list 885.415 114.7314) 
(list 959.4375 114.3814)))
(apply 'command (append '("pline") coords '("c")))
(setq currobj (ssadd (entlast) currobj))
(setq coords (list 
(list 959.4375 114.2384) 
(list 885.415 114.5884) 
(list 885.415 114.4114) 
(list 959.4375 114.1614)))
(apply 'command (append '("pline") coords '("c")))
(setq currobj (ssadd (entlast) currobj))
(setq coords (list 
(list 959.4375 114.0184) 
(list 885.415 114.2684) 
(list 885.415 114.0914) 
(list 959.4375 113.9414)))
(apply 'command (append '("pline") coords '("c")))
(setq currobj (ssadd (entlast) currobj))
(setq coords (list 
(list 959.4375 113.7984) 
(list 885.415 113.9484) 
(list 885.415 113.7714) 
(list 959.4375 113.7214)))
(apply 'command (append '("pline") coords '("c")))
(setq currobj (ssadd (entlast) currobj))
(setq coords (list 
(list 959.4375 113.5784) 
(list 885.415 113.6284) 
(list 885.415 113.4514) 
(list 959.4375 113.5014)))
(apply 'command (append '("pline") coords '("c")))
(setq currobj (ssadd (entlast) currobj))
(setq coords (list 
(list 959.4375 113.3584) 
(list 885.415 113.3084) 
(list 885.415 113.1314) 
(list 959.4375 113.2814)))
(apply 'command (append '("pline") coords '("c")))
(setq currobj (ssadd (entlast) currobj))
(setq coords (list 
(list 959.4375 113.1384) 
(list 885.415 112.9884) 
(list 885.415 112.8114) 
(list 959.4375 113.0614)))
(apply 'command (append '("pline") coords '("c")))
(setq currobj (ssadd (entlast) currobj))
(setq coords (list 
(list 959.4375 112.9184) 
(list 885.415 112.6684) 
(list 885.415 112.4914) 
(list 959.4375 112.8414)))
(apply 'command (append '("pline") coords '("c")))
(setq currobj (ssadd (entlast) currobj))
(setq coords (list 
(list 959.4375 112.6984) 
(list 885.415 112.3484) 
(list 885.415 112.1714) 
(list 959.4375 112.6214)))
(apply 'command (append '("pline") coords '("c")))
(setq currobj (ssadd (entlast) currobj))
(setq coords (list 
(list 959.4375 112.4784) 
(list 885.415 112.0284) 
(list 885.415 111.8514) 
(list 959.4375 112.4014)))
(apply 'command (append '("pline") coords '("c")))
(setq currobj (ssadd (entlast) currobj))
(setq coords (list 
(list 959.4375 112.2584) 
(list 885.415 111.7084) 
(list 885.415 111.5314) 
(list 959.4375 112.1814)))
(apply 'command (append '("pline") coords '("c")))
(setq currobj (ssadd (entlast) currobj))
(setq coords (list 
(list 959.4375 112.0384) 
(list 885.415 111.3884) 
(list 885.415 111.2114) 
(list 959.4375 111.9614)))
(apply 'command (append '("pline") coords '("c")))
(setq currobj (ssadd (entlast) currobj))
(command "_layer" "set" "nitride" "")
(command "_layer" "set" "text" "")
(command "_circle" "959.0625,100.8184" "0.075")
(command "_circle" "959.0625,101.1184" "0.075")
(command "_circle" "959.0625,101.4184" "0.075")
(command "_circle" "959.0625,101.7184" "0.075")
(command "_circle" "959.0625,102.0184" "0.075")
(command "_circle" "958.7625,100.8184" "0.075")
(command "_circle" "958.7625,101.1184" "0.075")
(command "_circle" "958.7625,101.4184" "0.075")
(command "_circle" "958.7625,101.7184" "0.075")
(command "_circle" "958.7625,102.0184" "0.075")
(command "_circle" "958.4625,100.8184" "0.075")
(command "_circle" "958.4625,101.1184" "0.075")
(command "_circle" "958.4625,101.4184" "0.075")
(command "_circle" "958.4625,101.7184" "0.075")
(command "_circle" "958.4625,102.0184" "0.075")
(command "_circle" "958.1625,100.8184" "0.075")
(command "_circle" "958.1625,101.1184" "0.075")
(command "_circle" "958.1625,101.4184" "0.075")
(command "_circle" "958.1625,101.7184" "0.075")
(command "_circle" "958.1625,102.0184" "0.075")
(command "_circle" "957.8625,100.8184" "0.075")
(command "_circle" "957.8625,101.1184" "0.075")
(command "_circle" "957.8625,101.4184" "0.075")
(command "_circle" "957.8625,101.7184" "0.075")
(command "_circle" "957.8625,102.0184" "0.075")
(command "_layer" "set" "nitride" "")
(setq coords (list 
(list 960.2625 126.2614) 
(list 960.2625 241.9061) 
(list 959.7375 241.9061) 
(list 959.7375 126.2614)))
(apply 'command (append '("pline") coords '("c")))
(setq currobj (ssadd (entlast) currobj))
(command "_layer" "set" "prebias" "")
(command "_rectangle" "959.7375,126.2614" "960.2625,241.9061")
(setq currobj (ssadd (entlast) currobj))
(command "_layer" "set" "nitride" "")
(setq coords (list 
(list 960.2625 241.9061) 
(list 960.5625 251.9061) 
(list 960.5625 251.9061) 
(list 960.5625 252.9061) 
(list 1034.585 252.1561) 
(list 1034.585 257.0991) 
(list 960.5625 256.3491) 
(list 960.5625 257.3491) 
(list 960.5625 257.3491) 
(list 960.2625 267.3491) 
(list 959.7375 267.3491) 
(list 959.4375 257.3491) 
(list 959.4375 257.3491) 
(list 959.4375 256.3491) 
(list 885.415 257.0991) 
(list 885.415 252.1561) 
(list 959.4375 252.9061) 
(list 959.4375 251.9061) 
(list 959.4375 251.9061) 
(list 959.7375 241.9061)))
(apply 'command (append '("pline") coords '("c")))
(setq currobj (ssadd (entlast) currobj))
(command "_layer" "set" "prebias" "")
(setq coords (list 
(list 959.4375 241.9061) 
(list 959.4375 252.9061) 
(list 885.415 252.1561) 
(list 885.415 257.0991) 
(list 959.4375 256.3491) 
(list 959.4375 267.3491) 
(list 960.5625 267.3491) 
(list 960.5625 256.3491) 
(list 1034.585 257.0991) 
(list 1034.585 252.1561) 
(list 960.5625 252.9061) 
(list 960.5625 241.9061)))
(apply 'command (append '("pline") coords '("c")))
(setq currobj (ssadd (entlast) currobj))
(command "_layer" "set" "nitride" "")
(command "_layer" "set" "fda1" "")
(setq coords (list 
(list 960.5625 253.0491) 
(list 1034.585 252.2991) 
(list 1034.585 252.4761) 
(list 960.5625 253.1261)))
(apply 'command (append '("pline") coords '("c")))
(setq currobj (ssadd (entlast) currobj))
(setq coords (list 
(list 960.5625 253.2691) 
(list 1034.585 252.6191) 
(list 1034.585 252.7961) 
(list 960.5625 253.3461)))
(apply 'command (append '("pline") coords '("c")))
(setq currobj (ssadd (entlast) currobj))
(setq coords (list 
(list 960.5625 253.4891) 
(list 1034.585 252.9391) 
(list 1034.585 253.1161) 
(list 960.5625 253.5661)))
(apply 'command (append '("pline") coords '("c")))
(setq currobj (ssadd (entlast) currobj))
(setq coords (list 
(list 960.5625 253.7091) 
(list 1034.585 253.2591) 
(list 1034.585 253.4361) 
(list 960.5625 253.7861)))
(apply 'command (append '("pline") coords '("c")))
(setq currobj (ssadd (entlast) currobj))
(setq coords (list 
(list 960.5625 253.9291) 
(list 1034.585 253.5791) 
(list 1034.585 253.7561) 
(list 960.5625 254.0061)))
(apply 'command (append '("pline") coords '("c")))
(setq currobj (ssadd (entlast) currobj))
(setq coords (list 
(list 960.5625 254.1491) 
(list 1034.585 253.8991) 
(list 1034.585 254.0761) 
(list 960.5625 254.2261)))
(apply 'command (append '("pline") coords '("c")))
(setq currobj (ssadd (entlast) currobj))
(setq coords (list 
(list 960.5625 254.3691) 
(list 1034.585 254.2191) 
(list 1034.585 254.3961) 
(list 960.5625 254.4461)))
(apply 'command (append '("pline") coords '("c")))
(setq currobj (ssadd (entlast) currobj))
(setq coords (list 
(list 960.5625 254.5891) 
(list 1034.585 254.5391) 
(list 1034.585 254.7161) 
(list 960.5625 254.6661)))
(apply 'command (append '("pline") coords '("c")))
(setq currobj (ssadd (entlast) currobj))
(setq coords (list 
(list 960.5625 254.8091) 
(list 1034.585 254.8591) 
(list 1034.585 255.0361) 
(list 960.5625 254.8861)))
(apply 'command (append '("pline") coords '("c")))
(setq currobj (ssadd (entlast) currobj))
(setq coords (list 
(list 960.5625 255.0291) 
(list 1034.585 255.1791) 
(list 1034.585 255.3561) 
(list 960.5625 255.1061)))
(apply 'command (append '("pline") coords '("c")))
(setq currobj (ssadd (entlast) currobj))
(setq coords (list 
(list 960.5625 255.2491) 
(list 1034.585 255.4991) 
(list 1034.585 255.6761) 
(list 960.5625 255.3261)))
(apply 'command (append '("pline") coords '("c")))
(setq currobj (ssadd (entlast) currobj))
(setq coords (list 
(list 960.5625 255.4691) 
(list 1034.585 255.8191) 
(list 1034.585 255.9961) 
(list 960.5625 255.5461)))
(apply 'command (append '("pline") coords '("c")))
(setq currobj (ssadd (entlast) currobj))
(setq coords (list 
(list 960.5625 255.6891) 
(list 1034.585 256.1391) 
(list 1034.585 256.3161) 
(list 960.5625 255.7661)))
(apply 'command (append '("pline") coords '("c")))
(setq currobj (ssadd (entlast) currobj))
(setq coords (list 
(list 960.5625 255.9091) 
(list 1034.585 256.4591) 
(list 1034.585 256.6361) 
(list 960.5625 255.9861)))
(apply 'command (append '("pline") coords '("c")))
(setq currobj (ssadd (entlast) currobj))
(setq coords (list 
(list 960.5625 256.1291) 
(list 1034.585 256.7791) 
(list 1034.585 256.9561) 
(list 960.5625 256.2061)))
(apply 'command (append '("pline") coords '("c")))
(setq currobj (ssadd (entlast) currobj))
(setq coords (list 
(list 959.4375 256.2061) 
(list 885.415 256.9561) 
(list 885.415 256.7791) 
(list 959.4375 256.1291)))
(apply 'command (append '("pline") coords '("c")))
(setq currobj (ssadd (entlast) currobj))
(setq coords (list 
(list 959.4375 255.9861) 
(list 885.415 256.6361) 
(list 885.415 256.4591) 
(list 959.4375 255.9091)))
(apply 'command (append '("pline") coords '("c")))
(setq currobj (ssadd (entlast) currobj))
(setq coords (list 
(list 959.4375 255.7661) 
(list 885.415 256.3161) 
(list 885.415 256.1391) 
(list 959.4375 255.6891)))
(apply 'command (append '("pline") coords '("c")))
(setq currobj (ssadd (entlast) currobj))
(setq coords (list 
(list 959.4375 255.5461) 
(list 885.415 255.9961) 
(list 885.415 255.8191) 
(list 959.4375 255.4691)))
(apply 'command (append '("pline") coords '("c")))
(setq currobj (ssadd (entlast) currobj))
(setq coords (list 
(list 959.4375 255.3261) 
(list 885.415 255.6761) 
(list 885.415 255.4991) 
(list 959.4375 255.2491)))
(apply 'command (append '("pline") coords '("c")))
(setq currobj (ssadd (entlast) currobj))
(setq coords (list 
(list 959.4375 255.1061) 
(list 885.415 255.3561) 
(list 885.415 255.1791) 
(list 959.4375 255.0291)))
(apply 'command (append '("pline") coords '("c")))
(setq currobj (ssadd (entlast) currobj))
(setq coords (list 
(list 959.4375 254.8861) 
(list 885.415 255.0361) 
(list 885.415 254.8591) 
(list 959.4375 254.8091)))
(apply 'command (append '("pline") coords '("c")))
(setq currobj (ssadd (entlast) currobj))
(setq coords (list 
(list 959.4375 254.6661) 
(list 885.415 254.7161) 
(list 885.415 254.5391) 
(list 959.4375 254.5891)))
(apply 'command (append '("pline") coords '("c")))
(setq currobj (ssadd (entlast) currobj))
(setq coords (list 
(list 959.4375 254.4461) 
(list 885.415 254.3961) 
(list 885.415 254.2191) 
(list 959.4375 254.3691)))
(apply 'command (append '("pline") coords '("c")))
(setq currobj (ssadd (entlast) currobj))
(setq coords (list 
(list 959.4375 254.2261) 
(list 885.415 254.0761) 
(list 885.415 253.8991) 
(list 959.4375 254.1491)))
(apply 'command (append '("pline") coords '("c")))
(setq currobj (ssadd (entlast) currobj))
(setq coords (list 
(list 959.4375 254.0061) 
(list 885.415 253.7561) 
(list 885.415 253.5791) 
(list 959.4375 253.9291)))
(apply 'command (append '("pline") coords '("c")))
(setq currobj (ssadd (entlast) currobj))
(setq coords (list 
(list 959.4375 253.7861) 
(list 885.415 253.4361) 
(list 885.415 253.2591) 
(list 959.4375 253.7091)))
(apply 'command (append '("pline") coords '("c")))
(setq currobj (ssadd (entlast) currobj))
(setq coords (list 
(list 959.4375 253.5661) 
(list 885.415 253.1161) 
(list 885.415 252.9391) 
(list 959.4375 253.4891)))
(apply 'command (append '("pline") coords '("c")))
(setq currobj (ssadd (entlast) currobj))
(setq coords (list 
(list 959.4375 253.3461) 
(list 885.415 252.7961) 
(list 885.415 252.6191) 
(list 959.4375 253.2691)))
(apply 'command (append '("pline") coords '("c")))
(setq currobj (ssadd (entlast) currobj))
(setq coords (list 
(list 959.4375 253.1261) 
(list 885.415 252.4761) 
(list 885.415 252.2991) 
(list 959.4375 253.0491)))
(apply 'command (append '("pline") coords '("c")))
(setq currobj (ssadd (entlast) currobj))
(command "_layer" "set" "nitride" "")
(command "_layer" "set" "text" "")
(command "_circle" "959.0625,241.9061" "0.075")
(command "_circle" "959.0625,242.2061" "0.075")
(command "_circle" "959.0625,242.5061" "0.075")
(command "_circle" "959.0625,242.8061" "0.075")
(command "_circle" "959.0625,243.1061" "0.075")
(command "_circle" "958.7625,241.9061" "0.075")
(command "_circle" "958.7625,242.2061" "0.075")
(command "_circle" "958.7625,242.5061" "0.075")
(command "_circle" "958.7625,242.8061" "0.075")
(command "_circle" "958.7625,243.1061" "0.075")
(command "_circle" "958.4625,241.9061" "0.075")
(command "_circle" "958.4625,242.2061" "0.075")
(command "_circle" "958.4625,242.5061" "0.075")
(command "_circle" "958.4625,242.8061" "0.075")
(command "_circle" "958.4625,243.1061" "0.075")
(command "_circle" "958.1625,241.9061" "0.075")
(command "_circle" "958.1625,242.2061" "0.075")
(command "_circle" "958.1625,242.5061" "0.075")
(command "_circle" "958.1625,242.8061" "0.075")
(command "_circle" "958.1625,243.1061" "0.075")
(command "_circle" "957.8625,241.9061" "0.075")
(command "_circle" "957.8625,242.2061" "0.075")
(command "_circle" "957.8625,242.5061" "0.075")
(command "_circle" "957.8625,242.8061" "0.075")
(command "_circle" "957.8625,243.1061" "0.075")
(command "_layer" "set" "nitride" "")
(setq coords (list 
(list 960.2625 267.3491) 
(list 960.2625 382.9939) 
(list 959.7375 382.9939) 
(list 959.7375 267.3491)))
(apply 'command (append '("pline") coords '("c")))
(setq currobj (ssadd (entlast) currobj))
(command "_layer" "set" "prebias" "")
(command "_rectangle" "959.7375,267.3491" "960.2625,382.9939")
(setq currobj (ssadd (entlast) currobj))
(command "_layer" "set" "nitride" "")
(setq coords (list 
(list 960.2625 382.9939) 
(list 960.5625 392.9939) 
(list 960.5625 392.9939) 
(list 960.5625 393.9939) 
(list 1034.585 393.2439) 
(list 1034.585 398.1869) 
(list 960.5625 397.4369) 
(list 960.5625 398.4369) 
(list 960.5625 398.4369) 
(list 960.2625 408.4369) 
(list 959.7375 408.4369) 
(list 959.4375 398.4369) 
(list 959.4375 398.4369) 
(list 959.4375 397.4369) 
(list 885.415 398.1869) 
(list 885.415 393.2439) 
(list 959.4375 393.9939) 
(list 959.4375 392.9939) 
(list 959.4375 392.9939) 
(list 959.7375 382.9939)))
(apply 'command (append '("pline") coords '("c")))
(setq currobj (ssadd (entlast) currobj))
(command "_layer" "set" "prebias" "")
(setq coords (list 
(list 959.4375 382.9939) 
(list 959.4375 393.9939) 
(list 885.415 393.2439) 
(list 885.415 398.1869) 
(list 959.4375 397.4369) 
(list 959.4375 408.4369) 
(list 960.5625 408.4369) 
(list 960.5625 397.4369) 
(list 1034.585 398.1869) 
(list 1034.585 393.2439) 
(list 960.5625 393.9939) 
(list 960.5625 382.9939)))
(apply 'command (append '("pline") coords '("c")))
(setq currobj (ssadd (entlast) currobj))
(command "_layer" "set" "nitride" "")
(command "_layer" "set" "fda1" "")
(setq coords (list 
(list 960.5625 394.1369) 
(list 1034.585 393.3869) 
(list 1034.585 393.5639) 
(list 960.5625 394.2139)))
(apply 'command (append '("pline") coords '("c")))
(setq currobj (ssadd (entlast) currobj))
(setq coords (list 
(list 960.5625 394.3569) 
(list 1034.585 393.7069) 
(list 1034.585 393.8839) 
(list 960.5625 394.4339)))
(apply 'command (append '("pline") coords '("c")))
(setq currobj (ssadd (entlast) currobj))
(setq coords (list 
(list 960.5625 394.5769) 
(list 1034.585 394.0269) 
(list 1034.585 394.2039) 
(list 960.5625 394.6539)))
(apply 'command (append '("pline") coords '("c")))
(setq currobj (ssadd (entlast) currobj))
(setq coords (list 
(list 960.5625 394.7969) 
(list 1034.585 394.3469) 
(list 1034.585 394.5239) 
(list 960.5625 394.8739)))
(apply 'command (append '("pline") coords '("c")))
(setq currobj (ssadd (entlast) currobj))
(setq coords (list 
(list 960.5625 395.0169) 
(list 1034.585 394.6669) 
(list 1034.585 394.8439) 
(list 960.5625 395.0939)))
(apply 'command (append '("pline") coords '("c")))
(setq currobj (ssadd (entlast) currobj))
(setq coords (list 
(list 960.5625 395.2369) 
(list 1034.585 394.9869) 
(list 1034.585 395.1639) 
(list 960.5625 395.3139)))
(apply 'command (append '("pline") coords '("c")))
(setq currobj (ssadd (entlast) currobj))
(setq coords (list 
(list 960.5625 395.4569) 
(list 1034.585 395.3069) 
(list 1034.585 395.4839) 
(list 960.5625 395.5339)))
(apply 'command (append '("pline") coords '("c")))
(setq currobj (ssadd (entlast) currobj))
(setq coords (list 
(list 960.5625 395.6769) 
(list 1034.585 395.6269) 
(list 1034.585 395.8039) 
(list 960.5625 395.7539)))
(apply 'command (append '("pline") coords '("c")))
(setq currobj (ssadd (entlast) currobj))
(setq coords (list 
(list 960.5625 395.8969) 
(list 1034.585 395.9469) 
(list 1034.585 396.1239) 
(list 960.5625 395.9739)))
(apply 'command (append '("pline") coords '("c")))
(setq currobj (ssadd (entlast) currobj))
(setq coords (list 
(list 960.5625 396.1169) 
(list 1034.585 396.2669) 
(list 1034.585 396.4439) 
(list 960.5625 396.1939)))
(apply 'command (append '("pline") coords '("c")))
(setq currobj (ssadd (entlast) currobj))
(setq coords (list 
(list 960.5625 396.3369) 
(list 1034.585 396.5869) 
(list 1034.585 396.7639) 
(list 960.5625 396.4139)))
(apply 'command (append '("pline") coords '("c")))
(setq currobj (ssadd (entlast) currobj))
(setq coords (list 
(list 960.5625 396.5569) 
(list 1034.585 396.9069) 
(list 1034.585 397.0839) 
(list 960.5625 396.6339)))
(apply 'command (append '("pline") coords '("c")))
(setq currobj (ssadd (entlast) currobj))
(setq coords (list 
(list 960.5625 396.7769) 
(list 1034.585 397.2269) 
(list 1034.585 397.4039) 
(list 960.5625 396.8539)))
(apply 'command (append '("pline") coords '("c")))
(setq currobj (ssadd (entlast) currobj))
(setq coords (list 
(list 960.5625 396.9969) 
(list 1034.585 397.5469) 
(list 1034.585 397.7239) 
(list 960.5625 397.0739)))
(apply 'command (append '("pline") coords '("c")))
(setq currobj (ssadd (entlast) currobj))
(setq coords (list 
(list 960.5625 397.2169) 
(list 1034.585 397.8669) 
(list 1034.585 398.0439) 
(list 960.5625 397.2939)))
(apply 'command (append '("pline") coords '("c")))
(setq currobj (ssadd (entlast) currobj))
(setq coords (list 
(list 959.4375 397.2939) 
(list 885.415 398.0439) 
(list 885.415 397.8669) 
(list 959.4375 397.2169)))
(apply 'command (append '("pline") coords '("c")))
(setq currobj (ssadd (entlast) currobj))
(setq coords (list 
(list 959.4375 397.0739) 
(list 885.415 397.7239) 
(list 885.415 397.5469) 
(list 959.4375 396.9969)))
(apply 'command (append '("pline") coords '("c")))
(setq currobj (ssadd (entlast) currobj))
(setq coords (list 
(list 959.4375 396.8539) 
(list 885.415 397.4039) 
(list 885.415 397.2269) 
(list 959.4375 396.7769)))
(apply 'command (append '("pline") coords '("c")))
(setq currobj (ssadd (entlast) currobj))
(setq coords (list 
(list 959.4375 396.6339) 
(list 885.415 397.0839) 
(list 885.415 396.9069) 
(list 959.4375 396.5569)))
(apply 'command (append '("pline") coords '("c")))
(setq currobj (ssadd (entlast) currobj))
(setq coords (list 
(list 959.4375 396.4139) 
(list 885.415 396.7639) 
(list 885.415 396.5869) 
(list 959.4375 396.3369)))
(apply 'command (append '("pline") coords '("c")))
(setq currobj (ssadd (entlast) currobj))
(setq coords (list 
(list 959.4375 396.1939) 
(list 885.415 396.4439) 
(list 885.415 396.2669) 
(list 959.4375 396.1169)))
(apply 'command (append '("pline") coords '("c")))
(setq currobj (ssadd (entlast) currobj))
(setq coords (list 
(list 959.4375 395.9739) 
(list 885.415 396.1239) 
(list 885.415 395.9469) 
(list 959.4375 395.8969)))
(apply 'command (append '("pline") coords '("c")))
(setq currobj (ssadd (entlast) currobj))
(setq coords (list 
(list 959.4375 395.7539) 
(list 885.415 395.8039) 
(list 885.415 395.6269) 
(list 959.4375 395.6769)))
(apply 'command (append '("pline") coords '("c")))
(setq currobj (ssadd (entlast) currobj))
(setq coords (list 
(list 959.4375 395.5339) 
(list 885.415 395.4839) 
(list 885.415 395.3069) 
(list 959.4375 395.4569)))
(apply 'command (append '("pline") coords '("c")))
(setq currobj (ssadd (entlast) currobj))
(setq coords (list 
(list 959.4375 395.3139) 
(list 885.415 395.1639) 
(list 885.415 394.9869) 
(list 959.4375 395.2369)))
(apply 'command (append '("pline") coords '("c")))
(setq currobj (ssadd (entlast) currobj))
(setq coords (list 
(list 959.4375 395.0939) 
(list 885.415 394.8439) 
(list 885.415 394.6669) 
(list 959.4375 395.0169)))
(apply 'command (append '("pline") coords '("c")))
(setq currobj (ssadd (entlast) currobj))
(setq coords (list 
(list 959.4375 394.8739) 
(list 885.415 394.5239) 
(list 885.415 394.3469) 
(list 959.4375 394.7969)))
(apply 'command (append '("pline") coords '("c")))
(setq currobj (ssadd (entlast) currobj))
(setq coords (list 
(list 959.4375 394.6539) 
(list 885.415 394.2039) 
(list 885.415 394.0269) 
(list 959.4375 394.5769)))
(apply 'command (append '("pline") coords '("c")))
(setq currobj (ssadd (entlast) currobj))
(setq coords (list 
(list 959.4375 394.4339) 
(list 885.415 393.8839) 
(list 885.415 393.7069) 
(list 959.4375 394.3569)))
(apply 'command (append '("pline") coords '("c")))
(setq currobj (ssadd (entlast) currobj))
(setq coords (list 
(list 959.4375 394.2139) 
(list 885.415 393.5639) 
(list 885.415 393.3869) 
(list 959.4375 394.1369)))
(apply 'command (append '("pline") coords '("c")))
(setq currobj (ssadd (entlast) currobj))
(command "_layer" "set" "nitride" "")
(command "_layer" "set" "text" "")
(command "_circle" "959.0625,382.9939" "0.075")
(command "_circle" "959.0625,383.2939" "0.075")
(command "_circle" "959.0625,383.5939" "0.075")
(command "_circle" "959.0625,383.8939" "0.075")
(command "_circle" "959.0625,384.1939" "0.075")
(command "_circle" "958.7625,382.9939" "0.075")
(command "_circle" "958.7625,383.2939" "0.075")
(command "_circle" "958.7625,383.5939" "0.075")
(command "_circle" "958.7625,383.8939" "0.075")
(command "_circle" "958.7625,384.1939" "0.075")
(command "_circle" "958.4625,382.9939" "0.075")
(command "_circle" "958.4625,383.2939" "0.075")
(command "_circle" "958.4625,383.5939" "0.075")
(command "_circle" "958.4625,383.8939" "0.075")
(command "_circle" "958.4625,384.1939" "0.075")
(command "_circle" "958.1625,382.9939" "0.075")
(command "_circle" "958.1625,383.2939" "0.075")
(command "_circle" "958.1625,383.5939" "0.075")
(command "_circle" "958.1625,383.8939" "0.075")
(command "_circle" "958.1625,384.1939" "0.075")
(command "_circle" "957.8625,382.9939" "0.075")
(command "_circle" "957.8625,383.2939" "0.075")
(command "_circle" "957.8625,383.5939" "0.075")
(command "_circle" "957.8625,383.8939" "0.075")
(command "_circle" "957.8625,384.1939" "0.075")
(command "_layer" "set" "nitride" "")
(setq coords (list 
(list 960.2625 408.4369) 
(list 960.2625 524.0816) 
(list 959.7375 524.0816) 
(list 959.7375 408.4369)))
(apply 'command (append '("pline") coords '("c")))
(setq currobj (ssadd (entlast) currobj))
(command "_layer" "set" "prebias" "")
(command "_rectangle" "959.7375,408.4369" "960.2625,524.0816")
(setq currobj (ssadd (entlast) currobj))
(command "_layer" "set" "nitride" "")
(setq coords (list 
(list 960.2625 524.0816) 
(list 960.5625 534.0816) 
(list 960.5625 534.0816) 
(list 960.5625 535.0816) 
(list 1034.585 534.3316) 
(list 1034.585 539.2746) 
(list 960.5625 538.5246) 
(list 960.5625 539.5246) 
(list 960.5625 539.5246) 
(list 960.2625 549.5246) 
(list 959.7375 549.5246) 
(list 959.4375 539.5246) 
(list 959.4375 539.5246) 
(list 959.4375 538.5246) 
(list 885.415 539.2746) 
(list 885.415 534.3316) 
(list 959.4375 535.0816) 
(list 959.4375 534.0816) 
(list 959.4375 534.0816) 
(list 959.7375 524.0816)))
(apply 'command (append '("pline") coords '("c")))
(setq currobj (ssadd (entlast) currobj))
(command "_layer" "set" "prebias" "")
(setq coords (list 
(list 959.4375 524.0816) 
(list 959.4375 535.0816) 
(list 885.415 534.3316) 
(list 885.415 539.2746) 
(list 959.4375 538.5246) 
(list 959.4375 549.5246) 
(list 960.5625 549.5246) 
(list 960.5625 538.5246) 
(list 1034.585 539.2746) 
(list 1034.585 534.3316) 
(list 960.5625 535.0816) 
(list 960.5625 524.0816)))
(apply 'command (append '("pline") coords '("c")))
(setq currobj (ssadd (entlast) currobj))
(command "_layer" "set" "nitride" "")
(command "_layer" "set" "fda1" "")
(setq coords (list 
(list 960.5625 535.2246) 
(list 1034.585 534.4746) 
(list 1034.585 534.6516) 
(list 960.5625 535.3016)))
(apply 'command (append '("pline") coords '("c")))
(setq currobj (ssadd (entlast) currobj))
(setq coords (list 
(list 960.5625 535.4446) 
(list 1034.585 534.7946) 
(list 1034.585 534.9716) 
(list 960.5625 535.5216)))
(apply 'command (append '("pline") coords '("c")))
(setq currobj (ssadd (entlast) currobj))
(setq coords (list 
(list 960.5625 535.6646) 
(list 1034.585 535.1146) 
(list 1034.585 535.2916) 
(list 960.5625 535.7416)))
(apply 'command (append '("pline") coords '("c")))
(setq currobj (ssadd (entlast) currobj))
(setq coords (list 
(list 960.5625 535.8846) 
(list 1034.585 535.4346) 
(list 1034.585 535.6116) 
(list 960.5625 535.9616)))
(apply 'command (append '("pline") coords '("c")))
(setq currobj (ssadd (entlast) currobj))
(setq coords (list 
(list 960.5625 536.1046) 
(list 1034.585 535.7546) 
(list 1034.585 535.9316) 
(list 960.5625 536.1816)))
(apply 'command (append '("pline") coords '("c")))
(setq currobj (ssadd (entlast) currobj))
(setq coords (list 
(list 960.5625 536.3246) 
(list 1034.585 536.0746) 
(list 1034.585 536.2516) 
(list 960.5625 536.4016)))
(apply 'command (append '("pline") coords '("c")))
(setq currobj (ssadd (entlast) currobj))
(setq coords (list 
(list 960.5625 536.5446) 
(list 1034.585 536.3946) 
(list 1034.585 536.5716) 
(list 960.5625 536.6216)))
(apply 'command (append '("pline") coords '("c")))
(setq currobj (ssadd (entlast) currobj))
(setq coords (list 
(list 960.5625 536.7646) 
(list 1034.585 536.7146) 
(list 1034.585 536.8916) 
(list 960.5625 536.8416)))
(apply 'command (append '("pline") coords '("c")))
(setq currobj (ssadd (entlast) currobj))
(setq coords (list 
(list 960.5625 536.9846) 
(list 1034.585 537.0346) 
(list 1034.585 537.2116) 
(list 960.5625 537.0616)))
(apply 'command (append '("pline") coords '("c")))
(setq currobj (ssadd (entlast) currobj))
(setq coords (list 
(list 960.5625 537.2046) 
(list 1034.585 537.3546) 
(list 1034.585 537.5316) 
(list 960.5625 537.2816)))
(apply 'command (append '("pline") coords '("c")))
(setq currobj (ssadd (entlast) currobj))
(setq coords (list 
(list 960.5625 537.4246) 
(list 1034.585 537.6746) 
(list 1034.585 537.8516) 
(list 960.5625 537.5016)))
(apply 'command (append '("pline") coords '("c")))
(setq currobj (ssadd (entlast) currobj))
(setq coords (list 
(list 960.5625 537.6446) 
(list 1034.585 537.9946) 
(list 1034.585 538.1716) 
(list 960.5625 537.7216)))
(apply 'command (append '("pline") coords '("c")))
(setq currobj (ssadd (entlast) currobj))
(setq coords (list 
(list 960.5625 537.8646) 
(list 1034.585 538.3146) 
(list 1034.585 538.4916) 
(list 960.5625 537.9416)))
(apply 'command (append '("pline") coords '("c")))
(setq currobj (ssadd (entlast) currobj))
(setq coords (list 
(list 960.5625 538.0846) 
(list 1034.585 538.6346) 
(list 1034.585 538.8116) 
(list 960.5625 538.1616)))
(apply 'command (append '("pline") coords '("c")))
(setq currobj (ssadd (entlast) currobj))
(setq coords (list 
(list 960.5625 538.3046) 
(list 1034.585 538.9546) 
(list 1034.585 539.1316) 
(list 960.5625 538.3816)))
(apply 'command (append '("pline") coords '("c")))
(setq currobj (ssadd (entlast) currobj))
(setq coords (list 
(list 959.4375 538.3816) 
(list 885.415 539.1316) 
(list 885.415 538.9546) 
(list 959.4375 538.3046)))
(apply 'command (append '("pline") coords '("c")))
(setq currobj (ssadd (entlast) currobj))
(setq coords (list 
(list 959.4375 538.1616) 
(list 885.415 538.8116) 
(list 885.415 538.6346) 
(list 959.4375 538.0846)))
(apply 'command (append '("pline") coords '("c")))
(setq currobj (ssadd (entlast) currobj))
(setq coords (list 
(list 959.4375 537.9416) 
(list 885.415 538.4916) 
(list 885.415 538.3146) 
(list 959.4375 537.8646)))
(apply 'command (append '("pline") coords '("c")))
(setq currobj (ssadd (entlast) currobj))
(setq coords (list 
(list 959.4375 537.7216) 
(list 885.415 538.1716) 
(list 885.415 537.9946) 
(list 959.4375 537.6446)))
(apply 'command (append '("pline") coords '("c")))
(setq currobj (ssadd (entlast) currobj))
(setq coords (list 
(list 959.4375 537.5016) 
(list 885.415 537.8516) 
(list 885.415 537.6746) 
(list 959.4375 537.4246)))
(apply 'command (append '("pline") coords '("c")))
(setq currobj (ssadd (entlast) currobj))
(setq coords (list 
(list 959.4375 537.2816) 
(list 885.415 537.5316) 
(list 885.415 537.3546) 
(list 959.4375 537.2046)))
(apply 'command (append '("pline") coords '("c")))
(setq currobj (ssadd (entlast) currobj))
(setq coords (list 
(list 959.4375 537.0616) 
(list 885.415 537.2116) 
(list 885.415 537.0346) 
(list 959.4375 536.9846)))
(apply 'command (append '("pline") coords '("c")))
(setq currobj (ssadd (entlast) currobj))
(setq coords (list 
(list 959.4375 536.8416) 
(list 885.415 536.8916) 
(list 885.415 536.7146) 
(list 959.4375 536.7646)))
(apply 'command (append '("pline") coords '("c")))
(setq currobj (ssadd (entlast) currobj))
(setq coords (list 
(list 959.4375 536.6216) 
(list 885.415 536.5716) 
(list 885.415 536.3946) 
(list 959.4375 536.5446)))
(apply 'command (append '("pline") coords '("c")))
(setq currobj (ssadd (entlast) currobj))
(setq coords (list 
(list 959.4375 536.4016) 
(list 885.415 536.2516) 
(list 885.415 536.0746) 
(list 959.4375 536.3246)))
(apply 'command (append '("pline") coords '("c")))
(setq currobj (ssadd (entlast) currobj))
(setq coords (list 
(list 959.4375 536.1816) 
(list 885.415 535.9316) 
(list 885.415 535.7546) 
(list 959.4375 536.1046)))
(apply 'command (append '("pline") coords '("c")))
(setq currobj (ssadd (entlast) currobj))
(setq coords (list 
(list 959.4375 535.9616) 
(list 885.415 535.6116) 
(list 885.415 535.4346) 
(list 959.4375 535.8846)))
(apply 'command (append '("pline") coords '("c")))
(setq currobj (ssadd (entlast) currobj))
(setq coords (list 
(list 959.4375 535.7416) 
(list 885.415 535.2916) 
(list 885.415 535.1146) 
(list 959.4375 535.6646)))
(apply 'command (append '("pline") coords '("c")))
(setq currobj (ssadd (entlast) currobj))
(setq coords (list 
(list 959.4375 535.5216) 
(list 885.415 534.9716) 
(list 885.415 534.7946) 
(list 959.4375 535.4446)))
(apply 'command (append '("pline") coords '("c")))
(setq currobj (ssadd (entlast) currobj))
(setq coords (list 
(list 959.4375 535.3016) 
(list 885.415 534.6516) 
(list 885.415 534.4746) 
(list 959.4375 535.2246)))
(apply 'command (append '("pline") coords '("c")))
(setq currobj (ssadd (entlast) currobj))
(command "_layer" "set" "nitride" "")
(command "_layer" "set" "text" "")
(command "_circle" "959.0625,524.0816" "0.075")
(command "_circle" "959.0625,524.3816" "0.075")
(command "_circle" "959.0625,524.6816" "0.075")
(command "_circle" "959.0625,524.9816" "0.075")
(command "_circle" "959.0625,525.2816" "0.075")
(command "_circle" "958.7625,524.0816" "0.075")
(command "_circle" "958.7625,524.3816" "0.075")
(command "_circle" "958.7625,524.6816" "0.075")
(command "_circle" "958.7625,524.9816" "0.075")
(command "_circle" "958.7625,525.2816" "0.075")
(command "_circle" "958.4625,524.0816" "0.075")
(command "_circle" "958.4625,524.3816" "0.075")
(command "_circle" "958.4625,524.6816" "0.075")
(command "_circle" "958.4625,524.9816" "0.075")
(command "_circle" "958.4625,525.2816" "0.075")
(command "_circle" "958.1625,524.0816" "0.075")
(command "_circle" "958.1625,524.3816" "0.075")
(command "_circle" "958.1625,524.6816" "0.075")
(command "_circle" "958.1625,524.9816" "0.075")
(command "_circle" "958.1625,525.2816" "0.075")
(command "_circle" "957.8625,524.0816" "0.075")
(command "_circle" "957.8625,524.3816" "0.075")
(command "_circle" "957.8625,524.6816" "0.075")
(command "_circle" "957.8625,524.9816" "0.075")
(command "_circle" "957.8625,525.2816" "0.075")
(command "_layer" "set" "nitride" "")
(setq coords (list 
(list 960.2625 549.5246) 
(list 960.2625 665.1693) 
(list 959.7375 665.1693) 
(list 959.7375 549.5246)))
(apply 'command (append '("pline") coords '("c")))
(setq currobj (ssadd (entlast) currobj))
(command "_layer" "set" "prebias" "")
(command "_rectangle" "959.7375,549.5246" "960.2625,665.1693")
(setq currobj (ssadd (entlast) currobj))
(command "_layer" "set" "nitride" "")
(setq coords (list 
(list 960.2625 665.1693) 
(list 960.5625 675.1693) 
(list 960.5625 675.1693) 
(list 960.5625 676.1693) 
(list 1034.585 675.4193) 
(list 1034.585 680.3623) 
(list 960.5625 679.6123) 
(list 960.5625 680.6123) 
(list 960.5625 680.6123) 
(list 960.2625 690.6123) 
(list 959.7375 690.6123) 
(list 959.4375 680.6123) 
(list 959.4375 680.6123) 
(list 959.4375 679.6123) 
(list 885.415 680.3623) 
(list 885.415 675.4193) 
(list 959.4375 676.1693) 
(list 959.4375 675.1693) 
(list 959.4375 675.1693) 
(list 959.7375 665.1693)))
(apply 'command (append '("pline") coords '("c")))
(setq currobj (ssadd (entlast) currobj))
(command "_layer" "set" "prebias" "")
(setq coords (list 
(list 959.4375 665.1693) 
(list 959.4375 676.1693) 
(list 885.415 675.4193) 
(list 885.415 680.3623) 
(list 959.4375 679.6123) 
(list 959.4375 690.6123) 
(list 960.5625 690.6123) 
(list 960.5625 679.6123) 
(list 1034.585 680.3623) 
(list 1034.585 675.4193) 
(list 960.5625 676.1693) 
(list 960.5625 665.1693)))
(apply 'command (append '("pline") coords '("c")))
(setq currobj (ssadd (entlast) currobj))
(command "_layer" "set" "nitride" "")
(command "_layer" "set" "fda1" "")
(setq coords (list 
(list 960.5625 676.3123) 
(list 1034.585 675.5623) 
(list 1034.585 675.7393) 
(list 960.5625 676.3893)))
(apply 'command (append '("pline") coords '("c")))
(setq currobj (ssadd (entlast) currobj))
(setq coords (list 
(list 960.5625 676.5323) 
(list 1034.585 675.8823) 
(list 1034.585 676.0593) 
(list 960.5625 676.6093)))
(apply 'command (append '("pline") coords '("c")))
(setq currobj (ssadd (entlast) currobj))
(setq coords (list 
(list 960.5625 676.7523) 
(list 1034.585 676.2023) 
(list 1034.585 676.3793) 
(list 960.5625 676.8293)))
(apply 'command (append '("pline") coords '("c")))
(setq currobj (ssadd (entlast) currobj))
(setq coords (list 
(list 960.5625 676.9723) 
(list 1034.585 676.5223) 
(list 1034.585 676.6993) 
(list 960.5625 677.0493)))
(apply 'command (append '("pline") coords '("c")))
(setq currobj (ssadd (entlast) currobj))
(setq coords (list 
(list 960.5625 677.1923) 
(list 1034.585 676.8423) 
(list 1034.585 677.0193) 
(list 960.5625 677.2693)))
(apply 'command (append '("pline") coords '("c")))
(setq currobj (ssadd (entlast) currobj))
(setq coords (list 
(list 960.5625 677.4123) 
(list 1034.585 677.1623) 
(list 1034.585 677.3393) 
(list 960.5625 677.4893)))
(apply 'command (append '("pline") coords '("c")))
(setq currobj (ssadd (entlast) currobj))
(setq coords (list 
(list 960.5625 677.6323) 
(list 1034.585 677.4823) 
(list 1034.585 677.6593) 
(list 960.5625 677.7093)))
(apply 'command (append '("pline") coords '("c")))
(setq currobj (ssadd (entlast) currobj))
(setq coords (list 
(list 960.5625 677.8523) 
(list 1034.585 677.8023) 
(list 1034.585 677.9793) 
(list 960.5625 677.9293)))
(apply 'command (append '("pline") coords '("c")))
(setq currobj (ssadd (entlast) currobj))
(setq coords (list 
(list 960.5625 678.0723) 
(list 1034.585 678.1223) 
(list 1034.585 678.2993) 
(list 960.5625 678.1493)))
(apply 'command (append '("pline") coords '("c")))
(setq currobj (ssadd (entlast) currobj))
(setq coords (list 
(list 960.5625 678.2923) 
(list 1034.585 678.4423) 
(list 1034.585 678.6193) 
(list 960.5625 678.3693)))
(apply 'command (append '("pline") coords '("c")))
(setq currobj (ssadd (entlast) currobj))
(setq coords (list 
(list 960.5625 678.5123) 
(list 1034.585 678.7623) 
(list 1034.585 678.9393) 
(list 960.5625 678.5893)))
(apply 'command (append '("pline") coords '("c")))
(setq currobj (ssadd (entlast) currobj))
(setq coords (list 
(list 960.5625 678.7323) 
(list 1034.585 679.0823) 
(list 1034.585 679.2593) 
(list 960.5625 678.8093)))
(apply 'command (append '("pline") coords '("c")))
(setq currobj (ssadd (entlast) currobj))
(setq coords (list 
(list 960.5625 678.9523) 
(list 1034.585 679.4023) 
(list 1034.585 679.5793) 
(list 960.5625 679.0293)))
(apply 'command (append '("pline") coords '("c")))
(setq currobj (ssadd (entlast) currobj))
(setq coords (list 
(list 960.5625 679.1723) 
(list 1034.585 679.7223) 
(list 1034.585 679.8993) 
(list 960.5625 679.2493)))
(apply 'command (append '("pline") coords '("c")))
(setq currobj (ssadd (entlast) currobj))
(setq coords (list 
(list 960.5625 679.3923) 
(list 1034.585 680.0423) 
(list 1034.585 680.2193) 
(list 960.5625 679.4693)))
(apply 'command (append '("pline") coords '("c")))
(setq currobj (ssadd (entlast) currobj))
(setq coords (list 
(list 959.4375 679.4693) 
(list 885.415 680.2193) 
(list 885.415 680.0423) 
(list 959.4375 679.3923)))
(apply 'command (append '("pline") coords '("c")))
(setq currobj (ssadd (entlast) currobj))
(setq coords (list 
(list 959.4375 679.2493) 
(list 885.415 679.8993) 
(list 885.415 679.7223) 
(list 959.4375 679.1723)))
(apply 'command (append '("pline") coords '("c")))
(setq currobj (ssadd (entlast) currobj))
(setq coords (list 
(list 959.4375 679.0293) 
(list 885.415 679.5793) 
(list 885.415 679.4023) 
(list 959.4375 678.9523)))
(apply 'command (append '("pline") coords '("c")))
(setq currobj (ssadd (entlast) currobj))
(setq coords (list 
(list 959.4375 678.8093) 
(list 885.415 679.2593) 
(list 885.415 679.0823) 
(list 959.4375 678.7323)))
(apply 'command (append '("pline") coords '("c")))
(setq currobj (ssadd (entlast) currobj))
(setq coords (list 
(list 959.4375 678.5893) 
(list 885.415 678.9393) 
(list 885.415 678.7623) 
(list 959.4375 678.5123)))
(apply 'command (append '("pline") coords '("c")))
(setq currobj (ssadd (entlast) currobj))
(setq coords (list 
(list 959.4375 678.3693) 
(list 885.415 678.6193) 
(list 885.415 678.4423) 
(list 959.4375 678.2923)))
(apply 'command (append '("pline") coords '("c")))
(setq currobj (ssadd (entlast) currobj))
(setq coords (list 
(list 959.4375 678.1493) 
(list 885.415 678.2993) 
(list 885.415 678.1223) 
(list 959.4375 678.0723)))
(apply 'command (append '("pline") coords '("c")))
(setq currobj (ssadd (entlast) currobj))
(setq coords (list 
(list 959.4375 677.9293) 
(list 885.415 677.9793) 
(list 885.415 677.8023) 
(list 959.4375 677.8523)))
(apply 'command (append '("pline") coords '("c")))
(setq currobj (ssadd (entlast) currobj))
(setq coords (list 
(list 959.4375 677.7093) 
(list 885.415 677.6593) 
(list 885.415 677.4823) 
(list 959.4375 677.6323)))
(apply 'command (append '("pline") coords '("c")))
(setq currobj (ssadd (entlast) currobj))
(setq coords (list 
(list 959.4375 677.4893) 
(list 885.415 677.3393) 
(list 885.415 677.1623) 
(list 959.4375 677.4123)))
(apply 'command (append '("pline") coords '("c")))
(setq currobj (ssadd (entlast) currobj))
(setq coords (list 
(list 959.4375 677.2693) 
(list 885.415 677.0193) 
(list 885.415 676.8423) 
(list 959.4375 677.1923)))
(apply 'command (append '("pline") coords '("c")))
(setq currobj (ssadd (entlast) currobj))
(setq coords (list 
(list 959.4375 677.0493) 
(list 885.415 676.6993) 
(list 885.415 676.5223) 
(list 959.4375 676.9723)))
(apply 'command (append '("pline") coords '("c")))
(setq currobj (ssadd (entlast) currobj))
(setq coords (list 
(list 959.4375 676.8293) 
(list 885.415 676.3793) 
(list 885.415 676.2023) 
(list 959.4375 676.7523)))
(apply 'command (append '("pline") coords '("c")))
(setq currobj (ssadd (entlast) currobj))
(setq coords (list 
(list 959.4375 676.6093) 
(list 885.415 676.0593) 
(list 885.415 675.8823) 
(list 959.4375 676.5323)))
(apply 'command (append '("pline") coords '("c")))
(setq currobj (ssadd (entlast) currobj))
(setq coords (list 
(list 959.4375 676.3893) 
(list 885.415 675.7393) 
(list 885.415 675.5623) 
(list 959.4375 676.3123)))
(apply 'command (append '("pline") coords '("c")))
(setq currobj (ssadd (entlast) currobj))
(command "_layer" "set" "nitride" "")
(command "_layer" "set" "text" "")
(command "_circle" "959.0625,665.1693" "0.075")
(command "_circle" "959.0625,665.4693" "0.075")
(command "_circle" "959.0625,665.7693" "0.075")
(command "_circle" "959.0625,666.0693" "0.075")
(command "_circle" "959.0625,666.3693" "0.075")
(command "_circle" "958.7625,665.1693" "0.075")
(command "_circle" "958.7625,665.4693" "0.075")
(command "_circle" "958.7625,665.7693" "0.075")
(command "_circle" "958.7625,666.0693" "0.075")
(command "_circle" "958.7625,666.3693" "0.075")
(command "_circle" "958.4625,665.1693" "0.075")
(command "_circle" "958.4625,665.4693" "0.075")
(command "_circle" "958.4625,665.7693" "0.075")
(command "_circle" "958.4625,666.0693" "0.075")
(command "_circle" "958.4625,666.3693" "0.075")
(command "_circle" "958.1625,665.1693" "0.075")
(command "_circle" "958.1625,665.4693" "0.075")
(command "_circle" "958.1625,665.7693" "0.075")
(command "_circle" "958.1625,666.0693" "0.075")
(command "_circle" "958.1625,666.3693" "0.075")
(command "_circle" "957.8625,665.1693" "0.075")
(command "_circle" "957.8625,665.4693" "0.075")
(command "_circle" "957.8625,665.7693" "0.075")
(command "_circle" "957.8625,666.0693" "0.075")
(command "_circle" "957.8625,666.3693" "0.075")
(command "_layer" "set" "nitride" "")
(setq coords (list 
(list 960.2625 690.6123) 
(list 960.2625 806.257) 
(list 959.7375 806.257) 
(list 959.7375 690.6123)))
(apply 'command (append '("pline") coords '("c")))
(setq currobj (ssadd (entlast) currobj))
(command "_layer" "set" "prebias" "")
(command "_rectangle" "959.7375,690.6123" "960.2625,806.257")
(setq currobj (ssadd (entlast) currobj))
(command "_layer" "set" "nitride" "")
(setq coords (list 
(list 960.2625 806.257) 
(list 960.5625 816.257) 
(list 960.5625 816.257) 
(list 960.5625 817.257) 
(list 1034.585 816.507) 
(list 1034.585 821.45) 
(list 960.5625 820.7) 
(list 960.5625 821.7) 
(list 960.5625 821.7) 
(list 960.2625 831.7) 
(list 959.7375 831.7) 
(list 959.4375 821.7) 
(list 959.4375 821.7) 
(list 959.4375 820.7) 
(list 885.415 821.45) 
(list 885.415 816.507) 
(list 959.4375 817.257) 
(list 959.4375 816.257) 
(list 959.4375 816.257) 
(list 959.7375 806.257)))
(apply 'command (append '("pline") coords '("c")))
(setq currobj (ssadd (entlast) currobj))
(command "_layer" "set" "prebias" "")
(setq coords (list 
(list 959.4375 806.257) 
(list 959.4375 817.257) 
(list 885.415 816.507) 
(list 885.415 821.45) 
(list 959.4375 820.7) 
(list 959.4375 831.7) 
(list 960.5625 831.7) 
(list 960.5625 820.7) 
(list 1034.585 821.45) 
(list 1034.585 816.507) 
(list 960.5625 817.257) 
(list 960.5625 806.257)))
(apply 'command (append '("pline") coords '("c")))
(setq currobj (ssadd (entlast) currobj))
(command "_layer" "set" "nitride" "")
(command "_layer" "set" "fda1" "")
(setq coords (list 
(list 960.5625 817.4) 
(list 1034.585 816.65) 
(list 1034.585 816.827) 
(list 960.5625 817.477)))
(apply 'command (append '("pline") coords '("c")))
(setq currobj (ssadd (entlast) currobj))
(setq coords (list 
(list 960.5625 817.62) 
(list 1034.585 816.97) 
(list 1034.585 817.147) 
(list 960.5625 817.697)))
(apply 'command (append '("pline") coords '("c")))
(setq currobj (ssadd (entlast) currobj))
(setq coords (list 
(list 960.5625 817.84) 
(list 1034.585 817.29) 
(list 1034.585 817.467) 
(list 960.5625 817.917)))
(apply 'command (append '("pline") coords '("c")))
(setq currobj (ssadd (entlast) currobj))
(setq coords (list 
(list 960.5625 818.06) 
(list 1034.585 817.61) 
(list 1034.585 817.787) 
(list 960.5625 818.137)))
(apply 'command (append '("pline") coords '("c")))
(setq currobj (ssadd (entlast) currobj))
(setq coords (list 
(list 960.5625 818.28) 
(list 1034.585 817.93) 
(list 1034.585 818.107) 
(list 960.5625 818.357)))
(apply 'command (append '("pline") coords '("c")))
(setq currobj (ssadd (entlast) currobj))
(setq coords (list 
(list 960.5625 818.5) 
(list 1034.585 818.25) 
(list 1034.585 818.427) 
(list 960.5625 818.577)))
(apply 'command (append '("pline") coords '("c")))
(setq currobj (ssadd (entlast) currobj))
(setq coords (list 
(list 960.5625 818.72) 
(list 1034.585 818.57) 
(list 1034.585 818.747) 
(list 960.5625 818.797)))
(apply 'command (append '("pline") coords '("c")))
(setq currobj (ssadd (entlast) currobj))
(setq coords (list 
(list 960.5625 818.94) 
(list 1034.585 818.89) 
(list 1034.585 819.067) 
(list 960.5625 819.017)))
(apply 'command (append '("pline") coords '("c")))
(setq currobj (ssadd (entlast) currobj))
(setq coords (list 
(list 960.5625 819.16) 
(list 1034.585 819.21) 
(list 1034.585 819.387) 
(list 960.5625 819.237)))
(apply 'command (append '("pline") coords '("c")))
(setq currobj (ssadd (entlast) currobj))
(setq coords (list 
(list 960.5625 819.38) 
(list 1034.585 819.53) 
(list 1034.585 819.707) 
(list 960.5625 819.457)))
(apply 'command (append '("pline") coords '("c")))
(setq currobj (ssadd (entlast) currobj))
(setq coords (list 
(list 960.5625 819.6) 
(list 1034.585 819.85) 
(list 1034.585 820.027) 
(list 960.5625 819.677)))
(apply 'command (append '("pline") coords '("c")))
(setq currobj (ssadd (entlast) currobj))
(setq coords (list 
(list 960.5625 819.82) 
(list 1034.585 820.17) 
(list 1034.585 820.347) 
(list 960.5625 819.897)))
(apply 'command (append '("pline") coords '("c")))
(setq currobj (ssadd (entlast) currobj))
(setq coords (list 
(list 960.5625 820.04) 
(list 1034.585 820.49) 
(list 1034.585 820.667) 
(list 960.5625 820.117)))
(apply 'command (append '("pline") coords '("c")))
(setq currobj (ssadd (entlast) currobj))
(setq coords (list 
(list 960.5625 820.26) 
(list 1034.585 820.81) 
(list 1034.585 820.987) 
(list 960.5625 820.337)))
(apply 'command (append '("pline") coords '("c")))
(setq currobj (ssadd (entlast) currobj))
(setq coords (list 
(list 960.5625 820.48) 
(list 1034.585 821.13) 
(list 1034.585 821.307) 
(list 960.5625 820.557)))
(apply 'command (append '("pline") coords '("c")))
(setq currobj (ssadd (entlast) currobj))
(setq coords (list 
(list 959.4375 820.557) 
(list 885.415 821.307) 
(list 885.415 821.13) 
(list 959.4375 820.48)))
(apply 'command (append '("pline") coords '("c")))
(setq currobj (ssadd (entlast) currobj))
(setq coords (list 
(list 959.4375 820.337) 
(list 885.415 820.987) 
(list 885.415 820.81) 
(list 959.4375 820.26)))
(apply 'command (append '("pline") coords '("c")))
(setq currobj (ssadd (entlast) currobj))
(setq coords (list 
(list 959.4375 820.117) 
(list 885.415 820.667) 
(list 885.415 820.49) 
(list 959.4375 820.04)))
(apply 'command (append '("pline") coords '("c")))
(setq currobj (ssadd (entlast) currobj))
(setq coords (list 
(list 959.4375 819.897) 
(list 885.415 820.347) 
(list 885.415 820.17) 
(list 959.4375 819.82)))
(apply 'command (append '("pline") coords '("c")))
(setq currobj (ssadd (entlast) currobj))
(setq coords (list 
(list 959.4375 819.677) 
(list 885.415 820.027) 
(list 885.415 819.85) 
(list 959.4375 819.6)))
(apply 'command (append '("pline") coords '("c")))
(setq currobj (ssadd (entlast) currobj))
(setq coords (list 
(list 959.4375 819.457) 
(list 885.415 819.707) 
(list 885.415 819.53) 
(list 959.4375 819.38)))
(apply 'command (append '("pline") coords '("c")))
(setq currobj (ssadd (entlast) currobj))
(setq coords (list 
(list 959.4375 819.237) 
(list 885.415 819.387) 
(list 885.415 819.21) 
(list 959.4375 819.16)))
(apply 'command (append '("pline") coords '("c")))
(setq currobj (ssadd (entlast) currobj))
(setq coords (list 
(list 959.4375 819.017) 
(list 885.415 819.067) 
(list 885.415 818.89) 
(list 959.4375 818.94)))
(apply 'command (append '("pline") coords '("c")))
(setq currobj (ssadd (entlast) currobj))
(setq coords (list 
(list 959.4375 818.797) 
(list 885.415 818.747) 
(list 885.415 818.57) 
(list 959.4375 818.72)))
(apply 'command (append '("pline") coords '("c")))
(setq currobj (ssadd (entlast) currobj))
(setq coords (list 
(list 959.4375 818.577) 
(list 885.415 818.427) 
(list 885.415 818.25) 
(list 959.4375 818.5)))
(apply 'command (append '("pline") coords '("c")))
(setq currobj (ssadd (entlast) currobj))
(setq coords (list 
(list 959.4375 818.357) 
(list 885.415 818.107) 
(list 885.415 817.93) 
(list 959.4375 818.28)))
(apply 'command (append '("pline") coords '("c")))
(setq currobj (ssadd (entlast) currobj))
(setq coords (list 
(list 959.4375 818.137) 
(list 885.415 817.787) 
(list 885.415 817.61) 
(list 959.4375 818.06)))
(apply 'command (append '("pline") coords '("c")))
(setq currobj (ssadd (entlast) currobj))
(setq coords (list 
(list 959.4375 817.917) 
(list 885.415 817.467) 
(list 885.415 817.29) 
(list 959.4375 817.84)))
(apply 'command (append '("pline") coords '("c")))
(setq currobj (ssadd (entlast) currobj))
(setq coords (list 
(list 959.4375 817.697) 
(list 885.415 817.147) 
(list 885.415 816.97) 
(list 959.4375 817.62)))
(apply 'command (append '("pline") coords '("c")))
(setq currobj (ssadd (entlast) currobj))
(setq coords (list 
(list 959.4375 817.477) 
(list 885.415 816.827) 
(list 885.415 816.65) 
(list 959.4375 817.4)))
(apply 'command (append '("pline") coords '("c")))
(setq currobj (ssadd (entlast) currobj))
(command "_layer" "set" "nitride" "")
(command "_layer" "set" "text" "")
(command "_circle" "959.0625,806.257" "0.075")
(command "_circle" "959.0625,806.557" "0.075")
(command "_circle" "959.0625,806.857" "0.075")
(command "_circle" "959.0625,807.157" "0.075")
(command "_circle" "959.0625,807.457" "0.075")
(command "_circle" "958.7625,806.257" "0.075")
(command "_circle" "958.7625,806.557" "0.075")
(command "_circle" "958.7625,806.857" "0.075")
(command "_circle" "958.7625,807.157" "0.075")
(command "_circle" "958.7625,807.457" "0.075")
(command "_circle" "958.4625,806.257" "0.075")
(command "_circle" "958.4625,806.557" "0.075")
(command "_circle" "958.4625,806.857" "0.075")
(command "_circle" "958.4625,807.157" "0.075")
(command "_circle" "958.4625,807.457" "0.075")
(command "_circle" "958.1625,806.257" "0.075")
(command "_circle" "958.1625,806.557" "0.075")
(command "_circle" "958.1625,806.857" "0.075")
(command "_circle" "958.1625,807.157" "0.075")
(command "_circle" "958.1625,807.457" "0.075")
(command "_circle" "957.8625,806.257" "0.075")
(command "_circle" "957.8625,806.557" "0.075")
(command "_circle" "957.8625,806.857" "0.075")
(command "_circle" "957.8625,807.157" "0.075")
(command "_circle" "957.8625,807.457" "0.075")
(command "_layer" "set" "nitride" "")
(setq coords (list 
(list 960.2625 831.7) 
(list 960.2625 836.7) 
(list 959.7375 836.7) 
(list 959.7375 831.7)))
(apply 'command (append '("pline") coords '("c")))
(setq currobj (ssadd (entlast) currobj))
(command "_layer" "set" "prebias" "")
(command "_rectangle" "959.7375,831.7" "960.2625,836.7")
(setq currobj (ssadd (entlast) currobj))
(command "_layer" "set" "nitride" "")
(setq cooledsinglenanobeam3 currobj)
(setq currobj nil)
(setq currobj (ssadd))
; DRAWING PHOTONIC CRYSTAL
(command "_layer" "set" "negYjunc" "")
(setq coords (list 
(list 960.125 866.7) 
(list 960 851.7) 
(list 960 866.7)))
(apply 'command (append '("pline") coords '("c")))
(setq currobj (ssadd (entlast) currobj))
(setq coords (list 
(list 960.2625 836.7) 
(list 960.405 866.7) 
(list 961.102 866.7) 
(list 961.102 836.7)))
(apply 'command (append '("pline") coords '("c")))
(setq currobj (ssadd (entlast) currobj))
(setq coords (list 
(list 959.875 866.7) 
(list 960 851.7) 
(list 960 866.7)))
(apply 'command (append '("pline") coords '("c")))
(setq currobj (ssadd (entlast) currobj))
(setq coords (list 
(list 959.7375 836.7) 
(list 959.595 866.7) 
(list 958.898 866.7) 
(list 958.898 836.7)))
(apply 'command (append '("pline") coords '("c")))
(setq currobj (ssadd (entlast) currobj))
(command "_layer" "set" "nitride" "")
(setq yjunction3 currobj)
(setq currobj nil)
(setq currobj (ssadd))
(setq tap3 nil)
(setq tap3 (ssadd))
(command "_layer" "set" "phc" "")
(setq coords (list 
(list 960 866.7) 
(list 960.125 866.7) 
(list 960.125 866.7103) 
(list 960.125 866.7206) 
(list 960.125 866.7308) 
(list 960.125 866.7411) 
(list 960.125 866.7514) 
(list 960.125 866.7617) 
(list 960.125 866.7719) 
(list 960.125 866.7822) 
(list 960.125 866.7925) 
(list 960.125 866.8028) 
(list 960.125 866.8131) 
(list 960.125 866.8233) 
(list 960.125 866.8336) 
(list 960.125 866.8439) 
(list 960.125 866.8542) 
(list 960.125 866.8644) 
(list 960.125 866.8747) 
(list 960.125 866.885) 
(list 960.125 866.8953) 
(list 960.125 866.9056) 
(list 960.125 866.9158) 
(list 960.125 866.9261) 
(list 960.125 866.9364) 
(list 960.125 866.9467) 
(list 960.125 866.9569) 
(list 960.125 866.9672) 
(list 960.125 866.9775) 
(list 960.125 866.9878) 
(list 960.125 866.9981) 
(list 960.125 867.0083) 
(list 960.125 867.0186) 
(list 960.125 867.0289) 
(list 960.125 867.0392) 
(list 960.125 867.0494) 
(list 960.125 867.0597) 
(list 960.125 867.07) 
(list 960 867.07)))
(apply 'command (append '("pline") coords '("c")))
(setq tap3 (ssadd (entlast) tap3))
(command "_mirror" (entlast) "" "960,900" "960,901" "No")
(setq tap3 (ssadd (entlast) tap3))
(setq coords (list 
(list 960.4147 866.7) 
(list 960.405 866.7) 
(list 960.4053 866.7103) 
(list 960.4055 866.7206) 
(list 960.4057 866.7308) 
(list 960.4058 866.7411) 
(list 960.4059 866.7514) 
(list 960.4059 866.7617) 
(list 960.4057 866.7719) 
(list 960.4055 866.7822) 
(list 960.4052 866.7925) 
(list 960.4047 866.8028) 
(list 960.4042 866.8131) 
(list 960.4037 866.8233) 
(list 960.4031 866.8336) 
(list 960.4025 866.8439) 
(list 960.402 866.8542) 
(list 960.4015 866.8644) 
(list 960.401 866.8747) 
(list 960.4007 866.885) 
(list 960.4006 866.8953) 
(list 960.4006 866.9056) 
(list 960.4007 866.9158) 
(list 960.4011 866.9261) 
(list 960.4016 866.9364) 
(list 960.4024 866.9467) 
(list 960.4032 866.9569) 
(list 960.4043 866.9672) 
(list 960.4054 866.9775) 
(list 960.4067 866.9878) 
(list 960.408 866.9981) 
(list 960.4093 867.0083) 
(list 960.4106 867.0186) 
(list 960.4118 867.0289) 
(list 960.4128 867.0392) 
(list 960.4137 867.0494) 
(list 960.4143 867.0597) 
(list 960.4147 867.07) 
(list 960.4147 867.07)))
(apply 'command (append '("pline") coords '("c")))
(setq tap3 (ssadd (entlast) tap3))
(command "_mirror" (entlast) "" "960,900" "960,901" "No")
(setq tap3 (ssadd (entlast) tap3))
(setq coords (list 
(list 961.102 866.7) 
(list 960.4147 866.7) 
(list 960.4147 866.7103) 
(list 960.4147 866.7206) 
(list 960.4147 866.7308) 
(list 960.4147 866.7411) 
(list 960.4147 866.7514) 
(list 960.4147 866.7617) 
(list 960.4147 866.7719) 
(list 960.4147 866.7822) 
(list 960.4147 866.7925) 
(list 960.4147 866.8028) 
(list 960.4147 866.8131) 
(list 960.4147 866.8233) 
(list 960.4147 866.8336) 
(list 960.4147 866.8439) 
(list 960.4147 866.8542) 
(list 960.4147 866.8644) 
(list 960.4147 866.8747) 
(list 960.4147 866.885) 
(list 960.4147 866.8953) 
(list 960.4147 866.9056) 
(list 960.4147 866.9158) 
(list 960.4147 866.9261) 
(list 960.4147 866.9364) 
(list 960.4147 866.9467) 
(list 960.4147 866.9569) 
(list 960.4147 866.9672) 
(list 960.4147 866.9775) 
(list 960.4147 866.9878) 
(list 960.4147 866.9981) 
(list 960.4147 867.0083) 
(list 960.4147 867.0186) 
(list 960.4147 867.0289) 
(list 960.4147 867.0392) 
(list 960.4147 867.0494) 
(list 960.4147 867.0597) 
(list 960.4147 867.07) 
(list 961.102 867.07)))
(apply 'command (append '("pline") coords '("c")))
(setq tap3 (ssadd (entlast) tap3))
(command "_mirror" (entlast) "" "960,900" "960,901" "No")
(setq tap3 (ssadd (entlast) tap3))
(setq coords (list 
(list 960 867.07) 
(list 960.125 867.07) 
(list 960.125 867.0803) 
(list 960.125 867.0906) 
(list 960.125 867.1008) 
(list 960.125 867.1111) 
(list 960.125 867.1214) 
(list 960.125 867.1317) 
(list 960.125 867.1419) 
(list 960.125 867.1522) 
(list 960.125 867.1625) 
(list 960.125 867.1728) 
(list 960.125 867.1831) 
(list 960.125 867.1933) 
(list 960.125 867.2036) 
(list 960.125 867.2139) 
(list 960.125 867.2242) 
(list 960.125 867.2344) 
(list 960.125 867.2447) 
(list 960.125 867.255) 
(list 960.125 867.2653) 
(list 960.125 867.2756) 
(list 960.125 867.2858) 
(list 960.125 867.2961) 
(list 960.125 867.3064) 
(list 960.125 867.3167) 
(list 960.125 867.3269) 
(list 960.125 867.3372) 
(list 960.125 867.3475) 
(list 960.125 867.3578) 
(list 960.125 867.3681) 
(list 960.125 867.3783) 
(list 960.125 867.3886) 
(list 960.125 867.3989) 
(list 960.125 867.4092) 
(list 960.125 867.4194) 
(list 960.125 867.4297) 
(list 960.125 867.44) 
(list 960 867.44)))
(apply 'command (append '("pline") coords '("c")))
(setq tap3 (ssadd (entlast) tap3))
(command "_mirror" (entlast) "" "960,900" "960,901" "No")
(setq tap3 (ssadd (entlast) tap3))
(setq coords (list 
(list 960.4245 867.07) 
(list 960.4147 867.07) 
(list 960.4149 867.0803) 
(list 960.4147 867.0906) 
(list 960.4142 867.1008) 
(list 960.4134 867.1111) 
(list 960.4124 867.1214) 
(list 960.411 867.1317) 
(list 960.4094 867.1419) 
(list 960.4077 867.1522) 
(list 960.4058 867.1625) 
(list 960.4037 867.1728) 
(list 960.4017 867.1831) 
(list 960.3997 867.1933) 
(list 960.3978 867.2036) 
(list 960.3961 867.2139) 
(list 960.3946 867.2242) 
(list 960.3935 867.2344) 
(list 960.3926 867.2447) 
(list 960.3922 867.255) 
(list 960.3922 867.2653) 
(list 960.3926 867.2756) 
(list 960.3934 867.2858) 
(list 960.3947 867.2961) 
(list 960.3964 867.3064) 
(list 960.3984 867.3167) 
(list 960.4007 867.3269) 
(list 960.4033 867.3372) 
(list 960.4061 867.3475) 
(list 960.4089 867.3578) 
(list 960.4117 867.3681) 
(list 960.4145 867.3783) 
(list 960.417 867.3886) 
(list 960.4193 867.3989) 
(list 960.4213 867.4092) 
(list 960.4229 867.4194) 
(list 960.4239 867.4297) 
(list 960.4245 867.44) 
(list 960.4245 867.44)))
(apply 'command (append '("pline") coords '("c")))
(setq tap3 (ssadd (entlast) tap3))
(command "_mirror" (entlast) "" "960,900" "960,901" "No")
(setq tap3 (ssadd (entlast) tap3))
(setq coords (list 
(list 961.102 867.07) 
(list 960.4245 867.07) 
(list 960.4245 867.0803) 
(list 960.4245 867.0906) 
(list 960.4245 867.1008) 
(list 960.4245 867.1111) 
(list 960.4245 867.1214) 
(list 960.4245 867.1317) 
(list 960.4245 867.1419) 
(list 960.4245 867.1522) 
(list 960.4245 867.1625) 
(list 960.4245 867.1728) 
(list 960.4245 867.1831) 
(list 960.4245 867.1933) 
(list 960.4245 867.2036) 
(list 960.4245 867.2139) 
(list 960.4245 867.2242) 
(list 960.4245 867.2344) 
(list 960.4245 867.2447) 
(list 960.4245 867.255) 
(list 960.4245 867.2653) 
(list 960.4245 867.2756) 
(list 960.4245 867.2858) 
(list 960.4245 867.2961) 
(list 960.4245 867.3064) 
(list 960.4245 867.3167) 
(list 960.4245 867.3269) 
(list 960.4245 867.3372) 
(list 960.4245 867.3475) 
(list 960.4245 867.3578) 
(list 960.4245 867.3681) 
(list 960.4245 867.3783) 
(list 960.4245 867.3886) 
(list 960.4245 867.3989) 
(list 960.4245 867.4092) 
(list 960.4245 867.4194) 
(list 960.4245 867.4297) 
(list 960.4245 867.44) 
(list 961.102 867.44)))
(apply 'command (append '("pline") coords '("c")))
(setq tap3 (ssadd (entlast) tap3))
(command "_mirror" (entlast) "" "960,900" "960,901" "No")
(setq tap3 (ssadd (entlast) tap3))
(setq coords (list 
(list 960 867.44) 
(list 960.125 867.44) 
(list 960.125 867.4503) 
(list 960.125 867.4606) 
(list 960.125 867.4708) 
(list 960.125 867.4811) 
(list 960.125 867.4914) 
(list 960.125 867.5017) 
(list 960.125 867.5119) 
(list 960.125 867.5222) 
(list 960.125 867.5325) 
(list 960.125 867.5428) 
(list 960.125 867.5531) 
(list 960.125 867.5633) 
(list 960.125 867.5736) 
(list 960.125 867.5839) 
(list 960.125 867.5942) 
(list 960.125 867.6044) 
(list 960.125 867.6147) 
(list 960.125 867.625) 
(list 960.125 867.6353) 
(list 960.125 867.6456) 
(list 960.125 867.6558) 
(list 960.125 867.6661) 
(list 960.125 867.6764) 
(list 960.125 867.6867) 
(list 960.125 867.6969) 
(list 960.125 867.7072) 
(list 960.125 867.7175) 
(list 960.125 867.7278) 
(list 960.125 867.7381) 
(list 960.125 867.7483) 
(list 960.125 867.7586) 
(list 960.125 867.7689) 
(list 960.125 867.7792) 
(list 960.125 867.7894) 
(list 960.125 867.7997) 
(list 960.125 867.81) 
(list 960 867.81)))
(apply 'command (append '("pline") coords '("c")))
(setq tap3 (ssadd (entlast) tap3))
(command "_mirror" (entlast) "" "960,900" "960,901" "No")
(setq tap3 (ssadd (entlast) tap3))
(setq coords (list 
(list 960.4342 867.44) 
(list 960.4245 867.44) 
(list 960.4245 867.4503) 
(list 960.4239 867.4606) 
(list 960.4227 867.4708) 
(list 960.421 867.4811) 
(list 960.4188 867.4914) 
(list 960.4162 867.5017) 
(list 960.4132 867.5119) 
(list 960.4099 867.5222) 
(list 960.4063 867.5325) 
(list 960.4028 867.5428) 
(list 960.3992 867.5531) 
(list 960.3957 867.5633) 
(list 960.3926 867.5736) 
(list 960.3897 867.5839) 
(list 960.3873 867.5942) 
(list 960.3855 867.6044) 
(list 960.3842 867.6147) 
(list 960.3837 867.625) 
(list 960.3838 867.6353) 
(list 960.3846 867.6456) 
(list 960.3861 867.6558) 
(list 960.3883 867.6661) 
(list 960.3911 867.6764) 
(list 960.3944 867.6867) 
(list 960.3982 867.6969) 
(list 960.4023 867.7072) 
(list 960.4067 867.7175) 
(list 960.4111 867.7278) 
(list 960.4154 867.7381) 
(list 960.4196 867.7483) 
(list 960.4235 867.7586) 
(list 960.4269 867.7689) 
(list 960.4298 867.7792) 
(list 960.432 867.7894) 
(list 960.4335 867.7997) 
(list 960.4342 867.81) 
(list 960.4342 867.81)))
(apply 'command (append '("pline") coords '("c")))
(setq tap3 (ssadd (entlast) tap3))
(command "_mirror" (entlast) "" "960,900" "960,901" "No")
(setq tap3 (ssadd (entlast) tap3))
(setq coords (list 
(list 961.102 867.44) 
(list 960.4342 867.44) 
(list 960.4342 867.4503) 
(list 960.4342 867.4606) 
(list 960.4342 867.4708) 
(list 960.4342 867.4811) 
(list 960.4342 867.4914) 
(list 960.4342 867.5017) 
(list 960.4342 867.5119) 
(list 960.4342 867.5222) 
(list 960.4342 867.5325) 
(list 960.4342 867.5428) 
(list 960.4342 867.5531) 
(list 960.4342 867.5633) 
(list 960.4342 867.5736) 
(list 960.4342 867.5839) 
(list 960.4342 867.5942) 
(list 960.4342 867.6044) 
(list 960.4342 867.6147) 
(list 960.4342 867.625) 
(list 960.4342 867.6353) 
(list 960.4342 867.6456) 
(list 960.4342 867.6558) 
(list 960.4342 867.6661) 
(list 960.4342 867.6764) 
(list 960.4342 867.6867) 
(list 960.4342 867.6969) 
(list 960.4342 867.7072) 
(list 960.4342 867.7175) 
(list 960.4342 867.7278) 
(list 960.4342 867.7381) 
(list 960.4342 867.7483) 
(list 960.4342 867.7586) 
(list 960.4342 867.7689) 
(list 960.4342 867.7792) 
(list 960.4342 867.7894) 
(list 960.4342 867.7997) 
(list 960.4342 867.81) 
(list 961.102 867.81)))
(apply 'command (append '("pline") coords '("c")))
(setq tap3 (ssadd (entlast) tap3))
(command "_mirror" (entlast) "" "960,900" "960,901" "No")
(setq tap3 (ssadd (entlast) tap3))
(setq coords (list 
(list 960 867.81) 
(list 960.125 867.81) 
(list 960.125 867.8203) 
(list 960.125 867.8306) 
(list 960.125 867.8408) 
(list 960.125 867.8511) 
(list 960.125 867.8614) 
(list 960.125 867.8717) 
(list 960.125 867.8819) 
(list 960.125 867.8922) 
(list 960.125 867.9025) 
(list 960.125 867.9128) 
(list 960.125 867.9231) 
(list 960.125 867.9333) 
(list 960.125 867.9436) 
(list 960.125 867.9539) 
(list 960.125 867.9642) 
(list 960.125 867.9744) 
(list 960.125 867.9847) 
(list 960.125 867.995) 
(list 960.125 868.0053) 
(list 960.125 868.0156) 
(list 960.125 868.0258) 
(list 960.125 868.0361) 
(list 960.125 868.0464) 
(list 960.125 868.0567) 
(list 960.125 868.0669) 
(list 960.125 868.0772) 
(list 960.125 868.0875) 
(list 960.125 868.0978) 
(list 960.125 868.1081) 
(list 960.125 868.1183) 
(list 960.125 868.1286) 
(list 960.125 868.1389) 
(list 960.125 868.1492) 
(list 960.125 868.1594) 
(list 960.125 868.1697) 
(list 960.125 868.18) 
(list 960 868.18)))
(apply 'command (append '("pline") coords '("c")))
(setq tap3 (ssadd (entlast) tap3))
(command "_mirror" (entlast) "" "960,900" "960,901" "No")
(setq tap3 (ssadd (entlast) tap3))
(setq coords (list 
(list 960.4439 867.81) 
(list 960.4342 867.81) 
(list 960.434 867.8203) 
(list 960.4331 867.8306) 
(list 960.4312 867.8408) 
(list 960.4286 867.8511) 
(list 960.4253 867.8614) 
(list 960.4214 867.8717) 
(list 960.4169 867.8819) 
(list 960.412 867.8922) 
(list 960.407 867.9025) 
(list 960.4018 867.9128) 
(list 960.3967 867.9231) 
(list 960.3918 867.9333) 
(list 960.3873 867.9436) 
(list 960.3833 867.9539) 
(list 960.38 867.9642) 
(list 960.3775 867.9744) 
(list 960.3759 867.9847) 
(list 960.3751 867.995) 
(list 960.3754 868.0053) 
(list 960.3766 868.0156) 
(list 960.3788 868.0258) 
(list 960.3819 868.0361) 
(list 960.3858 868.0464) 
(list 960.3905 868.0567) 
(list 960.3957 868.0669) 
(list 960.4013 868.0772) 
(list 960.4072 868.0875) 
(list 960.4133 868.0978) 
(list 960.4192 868.1081) 
(list 960.4248 868.1183) 
(list 960.43 868.1286) 
(list 960.4345 868.1389) 
(list 960.4383 868.1492) 
(list 960.4412 868.1594) 
(list 960.4431 868.1697) 
(list 960.4439 868.18) 
(list 960.4439 868.18)))
(apply 'command (append '("pline") coords '("c")))
(setq tap3 (ssadd (entlast) tap3))
(command "_mirror" (entlast) "" "960,900" "960,901" "No")
(setq tap3 (ssadd (entlast) tap3))
(setq coords (list 
(list 961.102 867.81) 
(list 960.4439 867.81) 
(list 960.4439 867.8203) 
(list 960.4439 867.8306) 
(list 960.4439 867.8408) 
(list 960.4439 867.8511) 
(list 960.4439 867.8614) 
(list 960.4439 867.8717) 
(list 960.4439 867.8819) 
(list 960.4439 867.8922) 
(list 960.4439 867.9025) 
(list 960.4439 867.9128) 
(list 960.4439 867.9231) 
(list 960.4439 867.9333) 
(list 960.4439 867.9436) 
(list 960.4439 867.9539) 
(list 960.4439 867.9642) 
(list 960.4439 867.9744) 
(list 960.4439 867.9847) 
(list 960.4439 867.995) 
(list 960.4439 868.0053) 
(list 960.4439 868.0156) 
(list 960.4439 868.0258) 
(list 960.4439 868.0361) 
(list 960.4439 868.0464) 
(list 960.4439 868.0567) 
(list 960.4439 868.0669) 
(list 960.4439 868.0772) 
(list 960.4439 868.0875) 
(list 960.4439 868.0978) 
(list 960.4439 868.1081) 
(list 960.4439 868.1183) 
(list 960.4439 868.1286) 
(list 960.4439 868.1389) 
(list 960.4439 868.1492) 
(list 960.4439 868.1594) 
(list 960.4439 868.1697) 
(list 960.4439 868.18) 
(list 961.102 868.18)))
(apply 'command (append '("pline") coords '("c")))
(setq tap3 (ssadd (entlast) tap3))
(command "_mirror" (entlast) "" "960,900" "960,901" "No")
(setq tap3 (ssadd (entlast) tap3))
(setq coords (list 
(list 960 868.18) 
(list 960.125 868.18) 
(list 960.125 868.1903) 
(list 960.125 868.2006) 
(list 960.125 868.2108) 
(list 960.125 868.2211) 
(list 960.125 868.2314) 
(list 960.125 868.2417) 
(list 960.125 868.2519) 
(list 960.125 868.2622) 
(list 960.125 868.2725) 
(list 960.125 868.2828) 
(list 960.125 868.2931) 
(list 960.125 868.3033) 
(list 960.125 868.3136) 
(list 960.125 868.3239) 
(list 960.125 868.3342) 
(list 960.125 868.3444) 
(list 960.125 868.3547) 
(list 960.125 868.365) 
(list 960.125 868.3753) 
(list 960.125 868.3856) 
(list 960.125 868.3958) 
(list 960.125 868.4061) 
(list 960.125 868.4164) 
(list 960.125 868.4267) 
(list 960.125 868.4369) 
(list 960.125 868.4472) 
(list 960.125 868.4575) 
(list 960.125 868.4678) 
(list 960.125 868.4781) 
(list 960.125 868.4883) 
(list 960.125 868.4986) 
(list 960.125 868.5089) 
(list 960.125 868.5192) 
(list 960.125 868.5294) 
(list 960.125 868.5397) 
(list 960.125 868.55) 
(list 960 868.55)))
(apply 'command (append '("pline") coords '("c")))
(setq tap3 (ssadd (entlast) tap3))
(command "_mirror" (entlast) "" "960,900" "960,901" "No")
(setq tap3 (ssadd (entlast) tap3))
(setq coords (list 
(list 960.4537 868.18) 
(list 960.4439 868.18) 
(list 960.4436 868.1903) 
(list 960.4422 868.2006) 
(list 960.4397 868.2108) 
(list 960.4362 868.2211) 
(list 960.4318 868.2314) 
(list 960.4265 868.2417) 
(list 960.4206 868.2519) 
(list 960.4142 868.2622) 
(list 960.4076 868.2725) 
(list 960.4008 868.2828) 
(list 960.3941 868.2931) 
(list 960.3878 868.3033) 
(list 960.382 868.3136) 
(list 960.3769 868.3239) 
(list 960.3727 868.3342) 
(list 960.3695 868.3444) 
(list 960.3675 868.3547) 
(list 960.3666 868.365) 
(list 960.367 868.3753) 
(list 960.3686 868.3856) 
(list 960.3715 868.3958) 
(list 960.3755 868.4061) 
(list 960.3805 868.4164) 
(list 960.3865 868.4267) 
(list 960.3932 868.4369) 
(list 960.4003 868.4472) 
(list 960.4079 868.4575) 
(list 960.4154 868.4678) 
(list 960.4229 868.4781) 
(list 960.43 868.4883) 
(list 960.4365 868.4986) 
(list 960.4421 868.5089) 
(list 960.4468 868.5192) 
(list 960.4504 868.5294) 
(list 960.4527 868.5397) 
(list 960.4537 868.55) 
(list 960.4537 868.55)))
(apply 'command (append '("pline") coords '("c")))
(setq tap3 (ssadd (entlast) tap3))
(command "_mirror" (entlast) "" "960,900" "960,901" "No")
(setq tap3 (ssadd (entlast) tap3))
(setq coords (list 
(list 961.102 868.18) 
(list 960.4537 868.18) 
(list 960.4537 868.1903) 
(list 960.4537 868.2006) 
(list 960.4537 868.2108) 
(list 960.4537 868.2211) 
(list 960.4537 868.2314) 
(list 960.4537 868.2417) 
(list 960.4537 868.2519) 
(list 960.4537 868.2622) 
(list 960.4537 868.2725) 
(list 960.4537 868.2828) 
(list 960.4537 868.2931) 
(list 960.4537 868.3033) 
(list 960.4537 868.3136) 
(list 960.4537 868.3239) 
(list 960.4537 868.3342) 
(list 960.4537 868.3444) 
(list 960.4537 868.3547) 
(list 960.4537 868.365) 
(list 960.4537 868.3753) 
(list 960.4537 868.3856) 
(list 960.4537 868.3958) 
(list 960.4537 868.4061) 
(list 960.4537 868.4164) 
(list 960.4537 868.4267) 
(list 960.4537 868.4369) 
(list 960.4537 868.4472) 
(list 960.4537 868.4575) 
(list 960.4537 868.4678) 
(list 960.4537 868.4781) 
(list 960.4537 868.4883) 
(list 960.4537 868.4986) 
(list 960.4537 868.5089) 
(list 960.4537 868.5192) 
(list 960.4537 868.5294) 
(list 960.4537 868.5397) 
(list 960.4537 868.55) 
(list 961.102 868.55)))
(apply 'command (append '("pline") coords '("c")))
(setq tap3 (ssadd (entlast) tap3))
(command "_mirror" (entlast) "" "960,900" "960,901" "No")
(setq tap3 (ssadd (entlast) tap3))
(setq coords (list 
(list 960 868.55) 
(list 960.125 868.55) 
(list 960.125 868.5603) 
(list 960.125 868.5706) 
(list 960.125 868.5808) 
(list 960.125 868.5911) 
(list 960.125 868.6014) 
(list 960.125 868.6117) 
(list 960.125 868.6219) 
(list 960.125 868.6322) 
(list 960.125 868.6425) 
(list 960.125 868.6528) 
(list 960.125 868.6631) 
(list 960.125 868.6733) 
(list 960.125 868.6836) 
(list 960.125 868.6939) 
(list 960.125 868.7042) 
(list 960.125 868.7144) 
(list 960.125 868.7247) 
(list 960.125 868.735) 
(list 960.125 868.7453) 
(list 960.125 868.7556) 
(list 960.125 868.7658) 
(list 960.125 868.7761) 
(list 960.125 868.7864) 
(list 960.125 868.7967) 
(list 960.125 868.8069) 
(list 960.125 868.8172) 
(list 960.125 868.8275) 
(list 960.125 868.8378) 
(list 960.125 868.8481) 
(list 960.125 868.8583) 
(list 960.125 868.8686) 
(list 960.125 868.8789) 
(list 960.125 868.8892) 
(list 960.125 868.8994) 
(list 960.125 868.9097) 
(list 960.125 868.92) 
(list 960 868.92)))
(apply 'command (append '("pline") coords '("c")))
(setq tap3 (ssadd (entlast) tap3))
(command "_mirror" (entlast) "" "960,900" "960,901" "No")
(setq tap3 (ssadd (entlast) tap3))
(setq coords (list 
(list 960.4634 868.55) 
(list 960.4537 868.55) 
(list 960.4532 868.5603) 
(list 960.4514 868.5706) 
(list 960.4483 868.5808) 
(list 960.4438 868.5911) 
(list 960.4383 868.6014) 
(list 960.4317 868.6117) 
(list 960.4243 868.6219) 
(list 960.4164 868.6322) 
(list 960.4081 868.6425) 
(list 960.3998 868.6528) 
(list 960.3916 868.6631) 
(list 960.3838 868.6733) 
(list 960.3767 868.6836) 
(list 960.3705 868.6939) 
(list 960.3654 868.7042) 
(list 960.3615 868.7144) 
(list 960.3591 868.7247) 
(list 960.3581 868.735) 
(list 960.3586 868.7453) 
(list 960.3607 868.7556) 
(list 960.3642 868.7658) 
(list 960.3691 868.7761) 
(list 960.3753 868.7864) 
(list 960.3825 868.7967) 
(list 960.3906 868.8069) 
(list 960.3994 868.8172) 
(list 960.4085 868.8275) 
(list 960.4176 868.8378) 
(list 960.4266 868.8481) 
(list 960.4351 868.8583) 
(list 960.4429 868.8686) 
(list 960.4497 868.8789) 
(list 960.4553 868.8892) 
(list 960.4596 868.8994) 
(list 960.4623 868.9097) 
(list 960.4634 868.92) 
(list 960.4634 868.92)))
(apply 'command (append '("pline") coords '("c")))
(setq tap3 (ssadd (entlast) tap3))
(command "_mirror" (entlast) "" "960,900" "960,901" "No")
(setq tap3 (ssadd (entlast) tap3))
(setq coords (list 
(list 961.102 868.55) 
(list 960.4634 868.55) 
(list 960.4634 868.5603) 
(list 960.4634 868.5706) 
(list 960.4634 868.5808) 
(list 960.4634 868.5911) 
(list 960.4634 868.6014) 
(list 960.4634 868.6117) 
(list 960.4634 868.6219) 
(list 960.4634 868.6322) 
(list 960.4634 868.6425) 
(list 960.4634 868.6528) 
(list 960.4634 868.6631) 
(list 960.4634 868.6733) 
(list 960.4634 868.6836) 
(list 960.4634 868.6939) 
(list 960.4634 868.7042) 
(list 960.4634 868.7144) 
(list 960.4634 868.7247) 
(list 960.4634 868.735) 
(list 960.4634 868.7453) 
(list 960.4634 868.7556) 
(list 960.4634 868.7658) 
(list 960.4634 868.7761) 
(list 960.4634 868.7864) 
(list 960.4634 868.7967) 
(list 960.4634 868.8069) 
(list 960.4634 868.8172) 
(list 960.4634 868.8275) 
(list 960.4634 868.8378) 
(list 960.4634 868.8481) 
(list 960.4634 868.8583) 
(list 960.4634 868.8686) 
(list 960.4634 868.8789) 
(list 960.4634 868.8892) 
(list 960.4634 868.8994) 
(list 960.4634 868.9097) 
(list 960.4634 868.92) 
(list 961.102 868.92)))
(apply 'command (append '("pline") coords '("c")))
(setq tap3 (ssadd (entlast) tap3))
(command "_mirror" (entlast) "" "960,900" "960,901" "No")
(setq tap3 (ssadd (entlast) tap3))
(setq coords (list 
(list 960 868.92) 
(list 960.125 868.92) 
(list 960.125 868.9303) 
(list 960.125 868.9406) 
(list 960.125 868.9508) 
(list 960.125 868.9611) 
(list 960.125 868.9714) 
(list 960.125 868.9817) 
(list 960.125 868.9919) 
(list 960.125 869.0022) 
(list 960.125 869.0125) 
(list 960.125 869.0228) 
(list 960.125 869.0331) 
(list 960.125 869.0433) 
(list 960.125 869.0536) 
(list 960.125 869.0639) 
(list 960.125 869.0742) 
(list 960.125 869.0844) 
(list 960.125 869.0947) 
(list 960.125 869.105) 
(list 960.125 869.1153) 
(list 960.125 869.1256) 
(list 960.125 869.1358) 
(list 960.125 869.1461) 
(list 960.125 869.1564) 
(list 960.125 869.1667) 
(list 960.125 869.1769) 
(list 960.125 869.1872) 
(list 960.125 869.1975) 
(list 960.125 869.2078) 
(list 960.125 869.2181) 
(list 960.125 869.2283) 
(list 960.125 869.2386) 
(list 960.125 869.2489) 
(list 960.125 869.2592) 
(list 960.125 869.2694) 
(list 960.125 869.2797) 
(list 960.125 869.29) 
(list 960 869.29)))
(apply 'command (append '("pline") coords '("c")))
(setq tap3 (ssadd (entlast) tap3))
(command "_mirror" (entlast) "" "960,900" "960,901" "No")
(setq tap3 (ssadd (entlast) tap3))
(setq coords (list 
(list 960.4731 868.92) 
(list 960.4634 868.92) 
(list 960.4628 868.9303) 
(list 960.4606 868.9406) 
(list 960.4568 868.9508) 
(list 960.4514 868.9611) 
(list 960.4447 868.9714) 
(list 960.4369 868.9817) 
(list 960.4281 868.9919) 
(list 960.4186 869.0022) 
(list 960.4088 869.0125) 
(list 960.3988 869.0228) 
(list 960.3891 869.0331) 
(list 960.3799 869.0433) 
(list 960.3715 869.0536) 
(list 960.3641 869.0639) 
(list 960.3581 869.0742) 
(list 960.3536 869.0844) 
(list 960.3507 869.0947) 
(list 960.3495 869.105) 
(list 960.3502 869.1153) 
(list 960.3527 869.1256) 
(list 960.3569 869.1358) 
(list 960.3627 869.1461) 
(list 960.37 869.1564) 
(list 960.3786 869.1667) 
(list 960.3881 869.1769) 
(list 960.3984 869.1872) 
(list 960.409 869.1975) 
(list 960.4198 869.2078) 
(list 960.4303 869.2181) 
(list 960.4403 869.2283) 
(list 960.4494 869.2386) 
(list 960.4573 869.2489) 
(list 960.4639 869.2592) 
(list 960.4688 869.2694) 
(list 960.4719 869.2797) 
(list 960.4731 869.29) 
(list 960.4731 869.29)))
(apply 'command (append '("pline") coords '("c")))
(setq tap3 (ssadd (entlast) tap3))
(command "_mirror" (entlast) "" "960,900" "960,901" "No")
(setq tap3 (ssadd (entlast) tap3))
(setq coords (list 
(list 961.102 868.92) 
(list 960.4731 868.92) 
(list 960.4731 868.9303) 
(list 960.4731 868.9406) 
(list 960.4731 868.9508) 
(list 960.4731 868.9611) 
(list 960.4731 868.9714) 
(list 960.4731 868.9817) 
(list 960.4731 868.9919) 
(list 960.4731 869.0022) 
(list 960.4731 869.0125) 
(list 960.4731 869.0228) 
(list 960.4731 869.0331) 
(list 960.4731 869.0433) 
(list 960.4731 869.0536) 
(list 960.4731 869.0639) 
(list 960.4731 869.0742) 
(list 960.4731 869.0844) 
(list 960.4731 869.0947) 
(list 960.4731 869.105) 
(list 960.4731 869.1153) 
(list 960.4731 869.1256) 
(list 960.4731 869.1358) 
(list 960.4731 869.1461) 
(list 960.4731 869.1564) 
(list 960.4731 869.1667) 
(list 960.4731 869.1769) 
(list 960.4731 869.1872) 
(list 960.4731 869.1975) 
(list 960.4731 869.2078) 
(list 960.4731 869.2181) 
(list 960.4731 869.2283) 
(list 960.4731 869.2386) 
(list 960.4731 869.2489) 
(list 960.4731 869.2592) 
(list 960.4731 869.2694) 
(list 960.4731 869.2797) 
(list 960.4731 869.29) 
(list 961.102 869.29)))
(apply 'command (append '("pline") coords '("c")))
(setq tap3 (ssadd (entlast) tap3))
(command "_mirror" (entlast) "" "960,900" "960,901" "No")
(setq tap3 (ssadd (entlast) tap3))
(setq coords (list 
(list 960 869.29) 
(list 960.125 869.29) 
(list 960.125 869.3003) 
(list 960.125 869.3106) 
(list 960.125 869.3208) 
(list 960.125 869.3311) 
(list 960.125 869.3414) 
(list 960.125 869.3517) 
(list 960.125 869.3619) 
(list 960.125 869.3722) 
(list 960.125 869.3825) 
(list 960.125 869.3928) 
(list 960.125 869.4031) 
(list 960.125 869.4133) 
(list 960.125 869.4236) 
(list 960.125 869.4339) 
(list 960.125 869.4442) 
(list 960.125 869.4544) 
(list 960.125 869.4647) 
(list 960.125 869.475) 
(list 960.125 869.4853) 
(list 960.125 869.4956) 
(list 960.125 869.5058) 
(list 960.125 869.5161) 
(list 960.125 869.5264) 
(list 960.125 869.5367) 
(list 960.125 869.5469) 
(list 960.125 869.5572) 
(list 960.125 869.5675) 
(list 960.125 869.5778) 
(list 960.125 869.5881) 
(list 960.125 869.5983) 
(list 960.125 869.6086) 
(list 960.125 869.6189) 
(list 960.125 869.6292) 
(list 960.125 869.6394) 
(list 960.125 869.6497) 
(list 960.125 869.66) 
(list 960 869.66)))
(apply 'command (append '("pline") coords '("c")))
(setq tap3 (ssadd (entlast) tap3))
(command "_mirror" (entlast) "" "960,900" "960,901" "No")
(setq tap3 (ssadd (entlast) tap3))
(setq coords (list 
(list 960.4829 869.29) 
(list 960.4731 869.29) 
(list 960.4724 869.3003) 
(list 960.4698 869.3106) 
(list 960.4653 869.3208) 
(list 960.459 869.3311) 
(list 960.4512 869.3414) 
(list 960.442 869.3517) 
(list 960.4318 869.3619) 
(list 960.4208 869.3722) 
(list 960.4094 869.3825) 
(list 960.3978 869.3928) 
(list 960.3866 869.4031) 
(list 960.3759 869.4133) 
(list 960.3662 869.4236) 
(list 960.3577 869.4339) 
(list 960.3508 869.4442) 
(list 960.3456 869.4544) 
(list 960.3423 869.4647) 
(list 960.341 869.475) 
(list 960.3418 869.4853) 
(list 960.3447 869.4956) 
(list 960.3496 869.5058) 
(list 960.3563 869.5161) 
(list 960.3647 869.5264) 
(list 960.3746 869.5367) 
(list 960.3856 869.5469) 
(list 960.3974 869.5572) 
(list 960.4097 869.5675) 
(list 960.422 869.5778) 
(list 960.4341 869.5881) 
(list 960.4455 869.5983) 
(list 960.4559 869.6086) 
(list 960.4649 869.6189) 
(list 960.4724 869.6292) 
(list 960.4779 869.6394) 
(list 960.4815 869.6497) 
(list 960.4829 869.66) 
(list 960.4829 869.66)))
(apply 'command (append '("pline") coords '("c")))
(setq tap3 (ssadd (entlast) tap3))
(command "_mirror" (entlast) "" "960,900" "960,901" "No")
(setq tap3 (ssadd (entlast) tap3))
(setq coords (list 
(list 961.102 869.29) 
(list 960.4829 869.29) 
(list 960.4829 869.3003) 
(list 960.4829 869.3106) 
(list 960.4829 869.3208) 
(list 960.4829 869.3311) 
(list 960.4829 869.3414) 
(list 960.4829 869.3517) 
(list 960.4829 869.3619) 
(list 960.4829 869.3722) 
(list 960.4829 869.3825) 
(list 960.4829 869.3928) 
(list 960.4829 869.4031) 
(list 960.4829 869.4133) 
(list 960.4829 869.4236) 
(list 960.4829 869.4339) 
(list 960.4829 869.4442) 
(list 960.4829 869.4544) 
(list 960.4829 869.4647) 
(list 960.4829 869.475) 
(list 960.4829 869.4853) 
(list 960.4829 869.4956) 
(list 960.4829 869.5058) 
(list 960.4829 869.5161) 
(list 960.4829 869.5264) 
(list 960.4829 869.5367) 
(list 960.4829 869.5469) 
(list 960.4829 869.5572) 
(list 960.4829 869.5675) 
(list 960.4829 869.5778) 
(list 960.4829 869.5881) 
(list 960.4829 869.5983) 
(list 960.4829 869.6086) 
(list 960.4829 869.6189) 
(list 960.4829 869.6292) 
(list 960.4829 869.6394) 
(list 960.4829 869.6497) 
(list 960.4829 869.66) 
(list 961.102 869.66)))
(apply 'command (append '("pline") coords '("c")))
(setq tap3 (ssadd (entlast) tap3))
(command "_mirror" (entlast) "" "960,900" "960,901" "No")
(setq tap3 (ssadd (entlast) tap3))
(setq coords (list 
(list 960 869.66) 
(list 960.125 869.66) 
(list 960.125 869.6703) 
(list 960.125 869.6806) 
(list 960.125 869.6908) 
(list 960.125 869.7011) 
(list 960.125 869.7114) 
(list 960.125 869.7217) 
(list 960.125 869.7319) 
(list 960.125 869.7422) 
(list 960.125 869.7525) 
(list 960.125 869.7628) 
(list 960.125 869.7731) 
(list 960.125 869.7833) 
(list 960.125 869.7936) 
(list 960.125 869.8039) 
(list 960.125 869.8142) 
(list 960.125 869.8244) 
(list 960.125 869.8347) 
(list 960.125 869.845) 
(list 960.125 869.8553) 
(list 960.125 869.8656) 
(list 960.125 869.8758) 
(list 960.125 869.8861) 
(list 960.125 869.8964) 
(list 960.125 869.9067) 
(list 960.125 869.9169) 
(list 960.125 869.9272) 
(list 960.125 869.9375) 
(list 960.125 869.9478) 
(list 960.125 869.9581) 
(list 960.125 869.9683) 
(list 960.125 869.9786) 
(list 960.125 869.9889) 
(list 960.125 869.9992) 
(list 960.125 870.0094) 
(list 960.125 870.0197) 
(list 960.125 870.03) 
(list 960 870.03)))
(apply 'command (append '("pline") coords '("c")))
(setq tap3 (ssadd (entlast) tap3))
(command "_mirror" (entlast) "" "960,900" "960,901" "No")
(setq tap3 (ssadd (entlast) tap3))
(setq coords (list 
(list 960.4926 869.66) 
(list 960.4829 869.66) 
(list 960.482 869.6703) 
(list 960.479 869.6806) 
(list 960.4738 869.6908) 
(list 960.4666 869.7011) 
(list 960.4577 869.7114) 
(list 960.4472 869.7217) 
(list 960.4355 869.7319) 
(list 960.423 869.7422) 
(list 960.4099 869.7525) 
(list 960.3968 869.7628) 
(list 960.384 869.7731) 
(list 960.3719 869.7833) 
(list 960.3609 869.7936) 
(list 960.3513 869.8039) 
(list 960.3435 869.8142) 
(list 960.3376 869.8244) 
(list 960.3339 869.8347) 
(list 960.3325 869.845) 
(list 960.3334 869.8553) 
(list 960.3367 869.8656) 
(list 960.3423 869.8758) 
(list 960.3499 869.8861) 
(list 960.3595 869.8964) 
(list 960.3706 869.9067) 
(list 960.3831 869.9169) 
(list 960.3964 869.9272) 
(list 960.4103 869.9375) 
(list 960.4242 869.9478) 
(list 960.4378 869.9581) 
(list 960.4506 869.9683) 
(list 960.4623 869.9786) 
(list 960.4725 869.9889) 
(list 960.4809 869.9992) 
(list 960.4871 870.0094) 
(list 960.4911 870.0197) 
(list 960.4926 870.03) 
(list 960.4926 870.03)))
(apply 'command (append '("pline") coords '("c")))
(setq tap3 (ssadd (entlast) tap3))
(command "_mirror" (entlast) "" "960,900" "960,901" "No")
(setq tap3 (ssadd (entlast) tap3))
(setq coords (list 
(list 961.102 869.66) 
(list 960.4926 869.66) 
(list 960.4926 869.6703) 
(list 960.4926 869.6806) 
(list 960.4926 869.6908) 
(list 960.4926 869.7011) 
(list 960.4926 869.7114) 
(list 960.4926 869.7217) 
(list 960.4926 869.7319) 
(list 960.4926 869.7422) 
(list 960.4926 869.7525) 
(list 960.4926 869.7628) 
(list 960.4926 869.7731) 
(list 960.4926 869.7833) 
(list 960.4926 869.7936) 
(list 960.4926 869.8039) 
(list 960.4926 869.8142) 
(list 960.4926 869.8244) 
(list 960.4926 869.8347) 
(list 960.4926 869.845) 
(list 960.4926 869.8553) 
(list 960.4926 869.8656) 
(list 960.4926 869.8758) 
(list 960.4926 869.8861) 
(list 960.4926 869.8964) 
(list 960.4926 869.9067) 
(list 960.4926 869.9169) 
(list 960.4926 869.9272) 
(list 960.4926 869.9375) 
(list 960.4926 869.9478) 
(list 960.4926 869.9581) 
(list 960.4926 869.9683) 
(list 960.4926 869.9786) 
(list 960.4926 869.9889) 
(list 960.4926 869.9992) 
(list 960.4926 870.0094) 
(list 960.4926 870.0197) 
(list 960.4926 870.03) 
(list 961.102 870.03)))
(apply 'command (append '("pline") coords '("c")))
(setq tap3 (ssadd (entlast) tap3))
(command "_mirror" (entlast) "" "960,900" "960,901" "No")
(setq tap3 (ssadd (entlast) tap3))
(setq coords (list 
(list 960 870.03) 
(list 960.125 870.03) 
(list 960.125 870.0403) 
(list 960.125 870.0506) 
(list 960.125 870.0608) 
(list 960.125 870.0711) 
(list 960.125 870.0814) 
(list 960.125 870.0917) 
(list 960.125 870.1019) 
(list 960.125 870.1122) 
(list 960.125 870.1225) 
(list 960.125 870.1328) 
(list 960.125 870.1431) 
(list 960.125 870.1533) 
(list 960.125 870.1636) 
(list 960.125 870.1739) 
(list 960.125 870.1842) 
(list 960.125 870.1944) 
(list 960.125 870.2047) 
(list 960.125 870.215) 
(list 960.125 870.2253) 
(list 960.125 870.2356) 
(list 960.125 870.2458) 
(list 960.125 870.2561) 
(list 960.125 870.2664) 
(list 960.125 870.2767) 
(list 960.125 870.2869) 
(list 960.125 870.2972) 
(list 960.125 870.3075) 
(list 960.125 870.3178) 
(list 960.125 870.3281) 
(list 960.125 870.3383) 
(list 960.125 870.3486) 
(list 960.125 870.3589) 
(list 960.125 870.3692) 
(list 960.125 870.3794) 
(list 960.125 870.3897) 
(list 960.125 870.4) 
(list 960 870.4)))
(apply 'command (append '("pline") coords '("c")))
(setq tap3 (ssadd (entlast) tap3))
(command "_mirror" (entlast) "" "960,900" "960,901" "No")
(setq tap3 (ssadd (entlast) tap3))
(setq coords (list 
(list 960.5023 870.03) 
(list 960.4926 870.03) 
(list 960.4916 870.0403) 
(list 960.4882 870.0506) 
(list 960.4823 870.0608) 
(list 960.4742 870.0711) 
(list 960.4641 870.0814) 
(list 960.4524 870.0917) 
(list 960.4392 870.1019) 
(list 960.4252 870.1122) 
(list 960.4105 870.1225) 
(list 960.3959 870.1328) 
(list 960.3815 870.1431) 
(list 960.368 870.1533) 
(list 960.3557 870.1636) 
(list 960.3449 870.1739) 
(list 960.3362 870.1842) 
(list 960.3296 870.1944) 
(list 960.3255 870.2047) 
(list 960.3239 870.215) 
(list 960.325 870.2253) 
(list 960.3287 870.2356) 
(list 960.3349 870.2458) 
(list 960.3435 870.2561) 
(list 960.3542 870.2664) 
(list 960.3667 870.2767) 
(list 960.3805 870.2869) 
(list 960.3954 870.2972) 
(list 960.4108 870.3075) 
(list 960.4264 870.3178) 
(list 960.4415 870.3281) 
(list 960.4558 870.3383) 
(list 960.4688 870.3486) 
(list 960.4801 870.3589) 
(list 960.4894 870.3692) 
(list 960.4963 870.3794) 
(list 960.5007 870.3897) 
(list 960.5023 870.4) 
(list 960.5023 870.4)))
(apply 'command (append '("pline") coords '("c")))
(setq tap3 (ssadd (entlast) tap3))
(command "_mirror" (entlast) "" "960,900" "960,901" "No")
(setq tap3 (ssadd (entlast) tap3))
(setq coords (list 
(list 961.102 870.03) 
(list 960.5023 870.03) 
(list 960.5023 870.0403) 
(list 960.5023 870.0506) 
(list 960.5023 870.0608) 
(list 960.5023 870.0711) 
(list 960.5023 870.0814) 
(list 960.5023 870.0917) 
(list 960.5023 870.1019) 
(list 960.5023 870.1122) 
(list 960.5023 870.1225) 
(list 960.5023 870.1328) 
(list 960.5023 870.1431) 
(list 960.5023 870.1533) 
(list 960.5023 870.1636) 
(list 960.5023 870.1739) 
(list 960.5023 870.1842) 
(list 960.5023 870.1944) 
(list 960.5023 870.2047) 
(list 960.5023 870.215) 
(list 960.5023 870.2253) 
(list 960.5023 870.2356) 
(list 960.5023 870.2458) 
(list 960.5023 870.2561) 
(list 960.5023 870.2664) 
(list 960.5023 870.2767) 
(list 960.5023 870.2869) 
(list 960.5023 870.2972) 
(list 960.5023 870.3075) 
(list 960.5023 870.3178) 
(list 960.5023 870.3281) 
(list 960.5023 870.3383) 
(list 960.5023 870.3486) 
(list 960.5023 870.3589) 
(list 960.5023 870.3692) 
(list 960.5023 870.3794) 
(list 960.5023 870.3897) 
(list 960.5023 870.4) 
(list 961.102 870.4)))
(apply 'command (append '("pline") coords '("c")))
(setq tap3 (ssadd (entlast) tap3))
(command "_mirror" (entlast) "" "960,900" "960,901" "No")
(setq tap3 (ssadd (entlast) tap3))
(setq coords (list 
(list 960 870.4) 
(list 960.125 870.4) 
(list 960.125 870.4103) 
(list 960.125 870.4206) 
(list 960.125 870.4308) 
(list 960.125 870.4411) 
(list 960.125 870.4514) 
(list 960.125 870.4617) 
(list 960.125 870.4719) 
(list 960.125 870.4822) 
(list 960.125 870.4925) 
(list 960.125 870.5028) 
(list 960.125 870.5131) 
(list 960.125 870.5233) 
(list 960.125 870.5336) 
(list 960.125 870.5439) 
(list 960.125 870.5542) 
(list 960.125 870.5644) 
(list 960.125 870.5747) 
(list 960.125 870.585) 
(list 960.125 870.5953) 
(list 960.125 870.6056) 
(list 960.125 870.6158) 
(list 960.125 870.6261) 
(list 960.125 870.6364) 
(list 960.125 870.6467) 
(list 960.125 870.6569) 
(list 960.125 870.6672) 
(list 960.125 870.6775) 
(list 960.125 870.6878) 
(list 960.125 870.6981) 
(list 960.125 870.7083) 
(list 960.125 870.7186) 
(list 960.125 870.7289) 
(list 960.125 870.7392) 
(list 960.125 870.7494) 
(list 960.125 870.7597) 
(list 960.125 870.77) 
(list 960 870.77)))
(apply 'command (append '("pline") coords '("c")))
(setq tap3 (ssadd (entlast) tap3))
(command "_mirror" (entlast) "" "960,900" "960,901" "No")
(setq tap3 (ssadd (entlast) tap3))
(setq coords (list 
(list 960.5121 870.4) 
(list 960.5023 870.4) 
(list 960.5012 870.4103) 
(list 960.4973 870.4206) 
(list 960.4908 870.4308) 
(list 960.4818 870.4411) 
(list 960.4706 870.4514) 
(list 960.4575 870.4617) 
(list 960.443 870.4719) 
(list 960.4273 870.4822) 
(list 960.4112 870.4925) 
(list 960.3949 870.5028) 
(list 960.379 870.5131) 
(list 960.364 870.5233) 
(list 960.3504 870.5336) 
(list 960.3385 870.5439) 
(list 960.3289 870.5542) 
(list 960.3216 870.5644) 
(list 960.3171 870.5747) 
(list 960.3154 870.585) 
(list 960.3166 870.5953) 
(list 960.3207 870.6056) 
(list 960.3276 870.6158) 
(list 960.3371 870.6261) 
(list 960.3489 870.6364) 
(list 960.3627 870.6467) 
(list 960.378 870.6569) 
(list 960.3944 870.6672) 
(list 960.4114 870.6775) 
(list 960.4286 870.6878) 
(list 960.4452 870.6981) 
(list 960.461 870.7083) 
(list 960.4753 870.7186) 
(list 960.4877 870.7289) 
(list 960.4979 870.7392) 
(list 960.5055 870.7494) 
(list 960.5103 870.7597) 
(list 960.5121 870.77) 
(list 960.5121 870.77)))
(apply 'command (append '("pline") coords '("c")))
(setq tap3 (ssadd (entlast) tap3))
(command "_mirror" (entlast) "" "960,900" "960,901" "No")
(setq tap3 (ssadd (entlast) tap3))
(setq coords (list 
(list 961.102 870.4) 
(list 960.5121 870.4) 
(list 960.5121 870.4103) 
(list 960.5121 870.4206) 
(list 960.5121 870.4308) 
(list 960.5121 870.4411) 
(list 960.5121 870.4514) 
(list 960.5121 870.4617) 
(list 960.5121 870.4719) 
(list 960.5121 870.4822) 
(list 960.5121 870.4925) 
(list 960.5121 870.5028) 
(list 960.5121 870.5131) 
(list 960.5121 870.5233) 
(list 960.5121 870.5336) 
(list 960.5121 870.5439) 
(list 960.5121 870.5542) 
(list 960.5121 870.5644) 
(list 960.5121 870.5747) 
(list 960.5121 870.585) 
(list 960.5121 870.5953) 
(list 960.5121 870.6056) 
(list 960.5121 870.6158) 
(list 960.5121 870.6261) 
(list 960.5121 870.6364) 
(list 960.5121 870.6467) 
(list 960.5121 870.6569) 
(list 960.5121 870.6672) 
(list 960.5121 870.6775) 
(list 960.5121 870.6878) 
(list 960.5121 870.6981) 
(list 960.5121 870.7083) 
(list 960.5121 870.7186) 
(list 960.5121 870.7289) 
(list 960.5121 870.7392) 
(list 960.5121 870.7494) 
(list 960.5121 870.7597) 
(list 960.5121 870.77) 
(list 961.102 870.77)))
(apply 'command (append '("pline") coords '("c")))
(setq tap3 (ssadd (entlast) tap3))
(command "_mirror" (entlast) "" "960,900" "960,901" "No")
(setq tap3 (ssadd (entlast) tap3))
(setq coords (list 
(list 960 870.77) 
(list 960.125 870.77) 
(list 960.125 870.7803) 
(list 960.125 870.7906) 
(list 960.125 870.8008) 
(list 960.125 870.8111) 
(list 960.125 870.8214) 
(list 960.125 870.8317) 
(list 960.125 870.8419) 
(list 960.125 870.8522) 
(list 960.125 870.8625) 
(list 960.125 870.8728) 
(list 960.125 870.8831) 
(list 960.125 870.8933) 
(list 960.125 870.9036) 
(list 960.125 870.9139) 
(list 960.125 870.9242) 
(list 960.125 870.9344) 
(list 960.125 870.9447) 
(list 960.125 870.955) 
(list 960.125 870.9653) 
(list 960.125 870.9756) 
(list 960.125 870.9858) 
(list 960.125 870.9961) 
(list 960.125 871.0064) 
(list 960.125 871.0167) 
(list 960.125 871.0269) 
(list 960.125 871.0372) 
(list 960.125 871.0475) 
(list 960.125 871.0578) 
(list 960.125 871.0681) 
(list 960.125 871.0783) 
(list 960.125 871.0886) 
(list 960.125 871.0989) 
(list 960.125 871.1092) 
(list 960.125 871.1194) 
(list 960.125 871.1297) 
(list 960.125 871.14) 
(list 960 871.14)))
(apply 'command (append '("pline") coords '("c")))
(setq tap3 (ssadd (entlast) tap3))
(command "_mirror" (entlast) "" "960,900" "960,901" "No")
(setq tap3 (ssadd (entlast) tap3))
(setq coords (list 
(list 960.5218 870.77) 
(list 960.5121 870.77) 
(list 960.5108 870.7803) 
(list 960.5065 870.7906) 
(list 960.4993 870.8008) 
(list 960.4894 870.8111) 
(list 960.4771 870.8214) 
(list 960.4627 870.8317) 
(list 960.4467 870.8419) 
(list 960.4295 870.8522) 
(list 960.4117 870.8625) 
(list 960.3939 870.8728) 
(list 960.3765 870.8831) 
(list 960.36 870.8933) 
(list 960.3451 870.9036) 
(list 960.3322 870.9139) 
(list 960.3215 870.9242) 
(list 960.3136 870.9344) 
(list 960.3087 870.9447) 
(list 960.3069 870.955) 
(list 960.3082 870.9653) 
(list 960.3128 870.9756) 
(list 960.3203 870.9858) 
(list 960.3307 870.9961) 
(list 960.3437 871.0064) 
(list 960.3587 871.0167) 
(list 960.3755 871.0269) 
(list 960.3934 871.0372) 
(list 960.4121 871.0475) 
(list 960.4307 871.0578) 
(list 960.449 871.0681) 
(list 960.4661 871.0783) 
(list 960.4818 871.0886) 
(list 960.4953 871.0989) 
(list 960.5064 871.1092) 
(list 960.5147 871.1194) 
(list 960.5199 871.1297) 
(list 960.5218 871.14) 
(list 960.5218 871.14)))
(apply 'command (append '("pline") coords '("c")))
(setq tap3 (ssadd (entlast) tap3))
(command "_mirror" (entlast) "" "960,900" "960,901" "No")
(setq tap3 (ssadd (entlast) tap3))
(setq coords (list 
(list 961.102 870.77) 
(list 960.5218 870.77) 
(list 960.5218 870.7803) 
(list 960.5218 870.7906) 
(list 960.5218 870.8008) 
(list 960.5218 870.8111) 
(list 960.5218 870.8214) 
(list 960.5218 870.8317) 
(list 960.5218 870.8419) 
(list 960.5218 870.8522) 
(list 960.5218 870.8625) 
(list 960.5218 870.8728) 
(list 960.5218 870.8831) 
(list 960.5218 870.8933) 
(list 960.5218 870.9036) 
(list 960.5218 870.9139) 
(list 960.5218 870.9242) 
(list 960.5218 870.9344) 
(list 960.5218 870.9447) 
(list 960.5218 870.955) 
(list 960.5218 870.9653) 
(list 960.5218 870.9756) 
(list 960.5218 870.9858) 
(list 960.5218 870.9961) 
(list 960.5218 871.0064) 
(list 960.5218 871.0167) 
(list 960.5218 871.0269) 
(list 960.5218 871.0372) 
(list 960.5218 871.0475) 
(list 960.5218 871.0578) 
(list 960.5218 871.0681) 
(list 960.5218 871.0783) 
(list 960.5218 871.0886) 
(list 960.5218 871.0989) 
(list 960.5218 871.1092) 
(list 960.5218 871.1194) 
(list 960.5218 871.1297) 
(list 960.5218 871.14) 
(list 961.102 871.14)))
(apply 'command (append '("pline") coords '("c")))
(setq tap3 (ssadd (entlast) tap3))
(command "_mirror" (entlast) "" "960,900" "960,901" "No")
(setq tap3 (ssadd (entlast) tap3))
(setq coords (list 
(list 960 871.14) 
(list 960.125 871.14) 
(list 960.125 871.1503) 
(list 960.125 871.1606) 
(list 960.125 871.1708) 
(list 960.125 871.1811) 
(list 960.125 871.1914) 
(list 960.125 871.2017) 
(list 960.125 871.2119) 
(list 960.125 871.2222) 
(list 960.125 871.2325) 
(list 960.125 871.2428) 
(list 960.125 871.2531) 
(list 960.125 871.2633) 
(list 960.125 871.2736) 
(list 960.125 871.2839) 
(list 960.125 871.2942) 
(list 960.125 871.3044) 
(list 960.125 871.3147) 
(list 960.125 871.325) 
(list 960.125 871.3353) 
(list 960.125 871.3456) 
(list 960.125 871.3558) 
(list 960.125 871.3661) 
(list 960.125 871.3764) 
(list 960.125 871.3867) 
(list 960.125 871.3969) 
(list 960.125 871.4072) 
(list 960.125 871.4175) 
(list 960.125 871.4278) 
(list 960.125 871.4381) 
(list 960.125 871.4483) 
(list 960.125 871.4586) 
(list 960.125 871.4689) 
(list 960.125 871.4792) 
(list 960.125 871.4894) 
(list 960.125 871.4997) 
(list 960.125 871.51) 
(list 960 871.51)))
(apply 'command (append '("pline") coords '("c")))
(setq tap3 (ssadd (entlast) tap3))
(command "_mirror" (entlast) "" "960,900" "960,901" "No")
(setq tap3 (ssadd (entlast) tap3))
(setq coords (list 
(list 960.5315 871.14) 
(list 960.5218 871.14) 
(list 960.5204 871.1503) 
(list 960.5157 871.1606) 
(list 960.5078 871.1708) 
(list 960.497 871.1811) 
(list 960.4835 871.1914) 
(list 960.4679 871.2017) 
(list 960.4504 871.2119) 
(list 960.4317 871.2222) 
(list 960.4123 871.2325) 
(list 960.3929 871.2428) 
(list 960.3739 871.2531) 
(list 960.3561 871.2633) 
(list 960.3398 871.2736) 
(list 960.3258 871.2839) 
(list 960.3142 871.2942) 
(list 960.3057 871.3044) 
(list 960.3003 871.3147) 
(list 960.2983 871.325) 
(list 960.2998 871.3353) 
(list 960.3048 871.3456) 
(list 960.313 871.3558) 
(list 960.3243 871.3661) 
(list 960.3384 871.3764) 
(list 960.3548 871.3867) 
(list 960.373 871.3969) 
(list 960.3925 871.4072) 
(list 960.4126 871.4175) 
(list 960.4329 871.4278) 
(list 960.4527 871.4381) 
(list 960.4713 871.4483) 
(list 960.4882 871.4586) 
(list 960.5029 871.4689) 
(list 960.5149 871.4792) 
(list 960.5239 871.4894) 
(list 960.5295 871.4997) 
(list 960.5315 871.51) 
(list 960.5315 871.51)))
(apply 'command (append '("pline") coords '("c")))
(setq tap3 (ssadd (entlast) tap3))
(command "_mirror" (entlast) "" "960,900" "960,901" "No")
(setq tap3 (ssadd (entlast) tap3))
(setq coords (list 
(list 961.102 871.14) 
(list 960.5315 871.14) 
(list 960.5315 871.1503) 
(list 960.5315 871.1606) 
(list 960.5315 871.1708) 
(list 960.5315 871.1811) 
(list 960.5315 871.1914) 
(list 960.5315 871.2017) 
(list 960.5315 871.2119) 
(list 960.5315 871.2222) 
(list 960.5315 871.2325) 
(list 960.5315 871.2428) 
(list 960.5315 871.2531) 
(list 960.5315 871.2633) 
(list 960.5315 871.2736) 
(list 960.5315 871.2839) 
(list 960.5315 871.2942) 
(list 960.5315 871.3044) 
(list 960.5315 871.3147) 
(list 960.5315 871.325) 
(list 960.5315 871.3353) 
(list 960.5315 871.3456) 
(list 960.5315 871.3558) 
(list 960.5315 871.3661) 
(list 960.5315 871.3764) 
(list 960.5315 871.3867) 
(list 960.5315 871.3969) 
(list 960.5315 871.4072) 
(list 960.5315 871.4175) 
(list 960.5315 871.4278) 
(list 960.5315 871.4381) 
(list 960.5315 871.4483) 
(list 960.5315 871.4586) 
(list 960.5315 871.4689) 
(list 960.5315 871.4792) 
(list 960.5315 871.4894) 
(list 960.5315 871.4997) 
(list 960.5315 871.51) 
(list 961.102 871.51)))
(apply 'command (append '("pline") coords '("c")))
(setq tap3 (ssadd (entlast) tap3))
(command "_mirror" (entlast) "" "960,900" "960,901" "No")
(setq tap3 (ssadd (entlast) tap3))
(setq coords (list 
(list 960 871.51) 
(list 960.125 871.51) 
(list 960.125 871.5203) 
(list 960.125 871.5306) 
(list 960.125 871.5408) 
(list 960.125 871.5511) 
(list 960.125 871.5614) 
(list 960.125 871.5717) 
(list 960.125 871.5819) 
(list 960.125 871.5922) 
(list 960.125 871.6025) 
(list 960.125 871.6128) 
(list 960.125 871.6231) 
(list 960.125 871.6333) 
(list 960.125 871.6436) 
(list 960.125 871.6539) 
(list 960.125 871.6642) 
(list 960.125 871.6744) 
(list 960.125 871.6847) 
(list 960.125 871.695) 
(list 960.125 871.7053) 
(list 960.125 871.7156) 
(list 960.125 871.7258) 
(list 960.125 871.7361) 
(list 960.125 871.7464) 
(list 960.125 871.7567) 
(list 960.125 871.7669) 
(list 960.125 871.7772) 
(list 960.125 871.7875) 
(list 960.125 871.7978) 
(list 960.125 871.8081) 
(list 960.125 871.8183) 
(list 960.125 871.8286) 
(list 960.125 871.8389) 
(list 960.125 871.8492) 
(list 960.125 871.8594) 
(list 960.125 871.8697) 
(list 960.125 871.88) 
(list 960 871.88)))
(apply 'command (append '("pline") coords '("c")))
(setq tap3 (ssadd (entlast) tap3))
(command "_mirror" (entlast) "" "960,900" "960,901" "No")
(setq tap3 (ssadd (entlast) tap3))
(setq coords (list 
(list 960.5413 871.51) 
(list 960.5315 871.51) 
(list 960.53 871.5203) 
(list 960.5249 871.5306) 
(list 960.5163 871.5408) 
(list 960.5046 871.5511) 
(list 960.49 871.5614) 
(list 960.473 871.5717) 
(list 960.4541 871.5819) 
(list 960.4339 871.5922) 
(list 960.413 871.6025) 
(list 960.3919 871.6128) 
(list 960.3714 871.6231) 
(list 960.3521 871.6333) 
(list 960.3346 871.6436) 
(list 960.3194 871.6539) 
(list 960.3069 871.6642) 
(list 960.2977 871.6744) 
(list 960.2919 871.6847) 
(list 960.2898 871.695) 
(list 960.2914 871.7053) 
(list 960.2968 871.7156) 
(list 960.3057 871.7258) 
(list 960.3179 871.7361) 
(list 960.3331 871.7464) 
(list 960.3508 871.7567) 
(list 960.3704 871.7669) 
(list 960.3915 871.7772) 
(list 960.4132 871.7875) 
(list 960.4351 871.7978) 
(list 960.4564 871.8081) 
(list 960.4765 871.8183) 
(list 960.4947 871.8286) 
(list 960.5105 871.8389) 
(list 960.5234 871.8492) 
(list 960.533 871.8594) 
(list 960.5391 871.8697) 
(list 960.5413 871.88) 
(list 960.5413 871.88)))
(apply 'command (append '("pline") coords '("c")))
(setq tap3 (ssadd (entlast) tap3))
(command "_mirror" (entlast) "" "960,900" "960,901" "No")
(setq tap3 (ssadd (entlast) tap3))
(setq coords (list 
(list 961.102 871.51) 
(list 960.5413 871.51) 
(list 960.5413 871.5203) 
(list 960.5413 871.5306) 
(list 960.5413 871.5408) 
(list 960.5413 871.5511) 
(list 960.5413 871.5614) 
(list 960.5413 871.5717) 
(list 960.5413 871.5819) 
(list 960.5413 871.5922) 
(list 960.5413 871.6025) 
(list 960.5413 871.6128) 
(list 960.5413 871.6231) 
(list 960.5413 871.6333) 
(list 960.5413 871.6436) 
(list 960.5413 871.6539) 
(list 960.5413 871.6642) 
(list 960.5413 871.6744) 
(list 960.5413 871.6847) 
(list 960.5413 871.695) 
(list 960.5413 871.7053) 
(list 960.5413 871.7156) 
(list 960.5413 871.7258) 
(list 960.5413 871.7361) 
(list 960.5413 871.7464) 
(list 960.5413 871.7567) 
(list 960.5413 871.7669) 
(list 960.5413 871.7772) 
(list 960.5413 871.7875) 
(list 960.5413 871.7978) 
(list 960.5413 871.8081) 
(list 960.5413 871.8183) 
(list 960.5413 871.8286) 
(list 960.5413 871.8389) 
(list 960.5413 871.8492) 
(list 960.5413 871.8594) 
(list 960.5413 871.8697) 
(list 960.5413 871.88) 
(list 961.102 871.88)))
(apply 'command (append '("pline") coords '("c")))
(setq tap3 (ssadd (entlast) tap3))
(command "_mirror" (entlast) "" "960,900" "960,901" "No")
(setq tap3 (ssadd (entlast) tap3))
(setq coords (list 
(list 960 871.88) 
(list 960.125 871.88) 
(list 960.125 871.8903) 
(list 960.125 871.9006) 
(list 960.125 871.9108) 
(list 960.125 871.9211) 
(list 960.125 871.9314) 
(list 960.125 871.9417) 
(list 960.125 871.9519) 
(list 960.125 871.9622) 
(list 960.125 871.9725) 
(list 960.125 871.9828) 
(list 960.125 871.9931) 
(list 960.125 872.0033) 
(list 960.125 872.0136) 
(list 960.125 872.0239) 
(list 960.125 872.0342) 
(list 960.125 872.0444) 
(list 960.125 872.0547) 
(list 960.125 872.065) 
(list 960.125 872.0753) 
(list 960.125 872.0856) 
(list 960.125 872.0958) 
(list 960.125 872.1061) 
(list 960.125 872.1164) 
(list 960.125 872.1267) 
(list 960.125 872.1369) 
(list 960.125 872.1472) 
(list 960.125 872.1575) 
(list 960.125 872.1678) 
(list 960.125 872.1781) 
(list 960.125 872.1883) 
(list 960.125 872.1986) 
(list 960.125 872.2089) 
(list 960.125 872.2192) 
(list 960.125 872.2294) 
(list 960.125 872.2397) 
(list 960.125 872.25) 
(list 960 872.25)))
(apply 'command (append '("pline") coords '("c")))
(setq tap3 (ssadd (entlast) tap3))
(command "_mirror" (entlast) "" "960,900" "960,901" "No")
(setq tap3 (ssadd (entlast) tap3))
(setq coords (list 
(list 960.551 871.88) 
(list 960.5413 871.88) 
(list 960.5396 871.8903) 
(list 960.5341 871.9006) 
(list 960.5248 871.9108) 
(list 960.5122 871.9211) 
(list 960.4965 871.9314) 
(list 960.4782 871.9417) 
(list 960.4579 871.9519) 
(list 960.4361 871.9622) 
(list 960.4135 871.9725) 
(list 960.3909 871.9828) 
(list 960.3689 871.9931) 
(list 960.3481 872.0033) 
(list 960.3293 872.0136) 
(list 960.313 872.0239) 
(list 960.2996 872.0342) 
(list 960.2897 872.0444) 
(list 960.2835 872.0547) 
(list 960.2813 872.065) 
(list 960.283 872.0753) 
(list 960.2888 872.0856) 
(list 960.2984 872.0958) 
(list 960.3115 872.1061) 
(list 960.3278 872.1164) 
(list 960.3468 872.1267) 
(list 960.3679 872.1369) 
(list 960.3905 872.1472) 
(list 960.4139 872.1575) 
(list 960.4373 872.1678) 
(list 960.4601 872.1781) 
(list 960.4816 872.1883) 
(list 960.5012 872.1986) 
(list 960.5181 872.2089) 
(list 960.5319 872.2192) 
(list 960.5422 872.2294) 
(list 960.5487 872.2397) 
(list 960.551 872.25) 
(list 960.551 872.25)))
(apply 'command (append '("pline") coords '("c")))
(setq tap3 (ssadd (entlast) tap3))
(command "_mirror" (entlast) "" "960,900" "960,901" "No")
(setq tap3 (ssadd (entlast) tap3))
(setq coords (list 
(list 961.102 871.88) 
(list 960.551 871.88) 
(list 960.551 871.8903) 
(list 960.551 871.9006) 
(list 960.551 871.9108) 
(list 960.551 871.9211) 
(list 960.551 871.9314) 
(list 960.551 871.9417) 
(list 960.551 871.9519) 
(list 960.551 871.9622) 
(list 960.551 871.9725) 
(list 960.551 871.9828) 
(list 960.551 871.9931) 
(list 960.551 872.0033) 
(list 960.551 872.0136) 
(list 960.551 872.0239) 
(list 960.551 872.0342) 
(list 960.551 872.0444) 
(list 960.551 872.0547) 
(list 960.551 872.065) 
(list 960.551 872.0753) 
(list 960.551 872.0856) 
(list 960.551 872.0958) 
(list 960.551 872.1061) 
(list 960.551 872.1164) 
(list 960.551 872.1267) 
(list 960.551 872.1369) 
(list 960.551 872.1472) 
(list 960.551 872.1575) 
(list 960.551 872.1678) 
(list 960.551 872.1781) 
(list 960.551 872.1883) 
(list 960.551 872.1986) 
(list 960.551 872.2089) 
(list 960.551 872.2192) 
(list 960.551 872.2294) 
(list 960.551 872.2397) 
(list 960.551 872.25) 
(list 961.102 872.25)))
(apply 'command (append '("pline") coords '("c")))
(setq tap3 (ssadd (entlast) tap3))
(command "_mirror" (entlast) "" "960,900" "960,901" "No")
(setq tap3 (ssadd (entlast) tap3))
(command "_block" "blktap3" "960,900" tap3 "")
(command "_insert" "blktap3" "960,900" "1" "1" "0")
(command "_insert" "blktap3" "960,900" "1" "1" "180")
(setq uc3 nil)
(setq uc3 (ssadd))
(setq coords (list 
(list 0 -0.185) 
(list 0.125 -0.185) 
(list 0.125 -0.17472) 
(list 0.125 -0.16444) 
(list 0.125 -0.15417) 
(list 0.125 -0.14389) 
(list 0.125 -0.13361) 
(list 0.125 -0.12333) 
(list 0.125 -0.11306) 
(list 0.125 -0.10278) 
(list 0.125 -0.0925) 
(list 0.125 -0.082222) 
(list 0.125 -0.071944) 
(list 0.125 -0.061667) 
(list 0.125 -0.051389) 
(list 0.125 -0.041111) 
(list 0.125 -0.030833) 
(list 0.125 -0.020556) 
(list 0.125 -0.010278) 
(list 0.125 0) 
(list 0.125 0.010278) 
(list 0.125 0.020556) 
(list 0.125 0.030833) 
(list 0.125 0.041111) 
(list 0.125 0.051389) 
(list 0.125 0.061667) 
(list 0.125 0.071944) 
(list 0.125 0.082222) 
(list 0.125 0.0925) 
(list 0.125 0.10278) 
(list 0.125 0.11306) 
(list 0.125 0.12333) 
(list 0.125 0.13361) 
(list 0.125 0.14389) 
(list 0.125 0.15417) 
(list 0.125 0.16444) 
(list 0.125 0.17472) 
(list 0.125 0.185) 
(list 0 0.185)))
(apply 'command (append '("pline") coords '("c")))
(setq uc3 (ssadd (entlast) uc3))
(setq coords (list 
(list 1.102 -0.185) 
(list 0.551 -0.185) 
(list 0.54892 -0.17472) 
(list 0.54274 -0.16444) 
(list 0.53265 -0.15417) 
(list 0.51895 -0.14389) 
(list 0.50206 -0.13361) 
(list 0.4825 -0.12333) 
(list 0.46086 -0.11306) 
(list 0.43779 -0.10278) 
(list 0.414 -0.0925) 
(list 0.39021 -0.082222) 
(list 0.36714 -0.071944) 
(list 0.3455 -0.061667) 
(list 0.32594 -0.051389) 
(list 0.30905 -0.041111) 
(list 0.29535 -0.030833) 
(list 0.28526 -0.020556) 
(list 0.27908 -0.010278) 
(list 0.277 0) 
(list 0.27908 0.010278) 
(list 0.28526 0.020556) 
(list 0.29535 0.030833) 
(list 0.30905 0.041111) 
(list 0.32594 0.051389) 
(list 0.3455 0.061667) 
(list 0.36714 0.071944) 
(list 0.39021 0.082222) 
(list 0.414 0.0925) 
(list 0.43779 0.10278) 
(list 0.46086 0.11306) 
(list 0.4825 0.12333) 
(list 0.50206 0.13361) 
(list 0.51895 0.14389) 
(list 0.53265 0.15417) 
(list 0.54274 0.16444) 
(list 0.54892 0.17472) 
(list 0.551 0.185) 
(list 1.102 0.185)))
(apply 'command (append '("pline") coords '("c")))
(setq uc3 (ssadd (entlast) uc3))
(command "_block" "blkuc3" "0,0.185" uc3 "")
(command "_insert" "blkuc3" "960,872.62" "1" "1" "0")
(command "_insert" "blkuc3" "960,872.25" "1" "1" "180")
(command "_insert" "blkuc3" "960,872.99" "1" "1" "0")
(command "_insert" "blkuc3" "960,872.62" "1" "1" "180")
(command "_insert" "blkuc3" "960,873.36" "1" "1" "0")
(command "_insert" "blkuc3" "960,872.99" "1" "1" "180")
(command "_insert" "blkuc3" "960,873.73" "1" "1" "0")
(command "_insert" "blkuc3" "960,873.36" "1" "1" "180")
(command "_insert" "blkuc3" "960,874.1" "1" "1" "0")
(command "_insert" "blkuc3" "960,873.73" "1" "1" "180")
(command "_insert" "blkuc3" "960,874.47" "1" "1" "0")
(command "_insert" "blkuc3" "960,874.1" "1" "1" "180")
(command "_insert" "blkuc3" "960,874.84" "1" "1" "0")
(command "_insert" "blkuc3" "960,874.47" "1" "1" "180")
(command "_insert" "blkuc3" "960,875.21" "1" "1" "0")
(command "_insert" "blkuc3" "960,874.84" "1" "1" "180")
(command "_insert" "blkuc3" "960,875.58" "1" "1" "0")
(command "_insert" "blkuc3" "960,875.21" "1" "1" "180")
(command "_insert" "blkuc3" "960,875.95" "1" "1" "0")
(command "_insert" "blkuc3" "960,875.58" "1" "1" "180")
(command "_insert" "blkuc3" "960,876.32" "1" "1" "0")
(command "_insert" "blkuc3" "960,875.95" "1" "1" "180")
(command "_insert" "blkuc3" "960,876.69" "1" "1" "0")
(command "_insert" "blkuc3" "960,876.32" "1" "1" "180")
(command "_insert" "blkuc3" "960,877.06" "1" "1" "0")
(command "_insert" "blkuc3" "960,876.69" "1" "1" "180")
(command "_insert" "blkuc3" "960,877.43" "1" "1" "0")
(command "_insert" "blkuc3" "960,877.06" "1" "1" "180")
(command "_insert" "blkuc3" "960,877.8" "1" "1" "0")
(command "_insert" "blkuc3" "960,877.43" "1" "1" "180")
(command "_insert" "blkuc3" "960,878.17" "1" "1" "0")
(command "_insert" "blkuc3" "960,877.8" "1" "1" "180")
(command "_insert" "blkuc3" "960,878.54" "1" "1" "0")
(command "_insert" "blkuc3" "960,878.17" "1" "1" "180")
(command "_insert" "blkuc3" "960,878.91" "1" "1" "0")
(command "_insert" "blkuc3" "960,878.54" "1" "1" "180")
(command "_insert" "blkuc3" "960,879.28" "1" "1" "0")
(command "_insert" "blkuc3" "960,878.91" "1" "1" "180")
(command "_insert" "blkuc3" "960,879.65" "1" "1" "0")
(command "_insert" "blkuc3" "960,879.28" "1" "1" "180")
(command "_insert" "blkuc3" "960,880.02" "1" "1" "0")
(command "_insert" "blkuc3" "960,879.65" "1" "1" "180")
(command "_insert" "blkuc3" "960,880.39" "1" "1" "0")
(command "_insert" "blkuc3" "960,880.02" "1" "1" "180")
(command "_insert" "blkuc3" "960,880.76" "1" "1" "0")
(command "_insert" "blkuc3" "960,880.39" "1" "1" "180")
(command "_insert" "blkuc3" "960,881.13" "1" "1" "0")
(command "_insert" "blkuc3" "960,880.76" "1" "1" "180")
(command "_insert" "blkuc3" "960,881.5" "1" "1" "0")
(command "_insert" "blkuc3" "960,881.13" "1" "1" "180")
(command "_insert" "blkuc3" "960,881.87" "1" "1" "0")
(command "_insert" "blkuc3" "960,881.5" "1" "1" "180")
(command "_insert" "blkuc3" "960,882.24" "1" "1" "0")
(command "_insert" "blkuc3" "960,881.87" "1" "1" "180")
(command "_insert" "blkuc3" "960,882.61" "1" "1" "0")
(command "_insert" "blkuc3" "960,882.24" "1" "1" "180")
(command "_insert" "blkuc3" "960,882.98" "1" "1" "0")
(command "_insert" "blkuc3" "960,882.61" "1" "1" "180")
(command "_insert" "blkuc3" "960,883.35" "1" "1" "0")
(command "_insert" "blkuc3" "960,882.98" "1" "1" "180")
(command "_insert" "blkuc3" "960,883.72" "1" "1" "0")
(command "_insert" "blkuc3" "960,883.35" "1" "1" "180")
(command "_insert" "blkuc3" "960,884.09" "1" "1" "0")
(command "_insert" "blkuc3" "960,883.72" "1" "1" "180")
(command "_insert" "blkuc3" "960,884.46" "1" "1" "0")
(command "_insert" "blkuc3" "960,884.09" "1" "1" "180")
(command "_insert" "blkuc3" "960,884.83" "1" "1" "0")
(command "_insert" "blkuc3" "960,884.46" "1" "1" "180")
(command "_insert" "blkuc3" "960,885.2" "1" "1" "0")
(command "_insert" "blkuc3" "960,884.83" "1" "1" "180")
(command "_insert" "blkuc3" "960,885.57" "1" "1" "0")
(command "_insert" "blkuc3" "960,885.2" "1" "1" "180")
(command "_insert" "blkuc3" "960,885.94" "1" "1" "0")
(command "_insert" "blkuc3" "960,885.57" "1" "1" "180")
(command "_insert" "blkuc3" "960,886.31" "1" "1" "0")
(command "_insert" "blkuc3" "960,885.94" "1" "1" "180")
(command "_insert" "blkuc3" "960,886.68" "1" "1" "0")
(command "_insert" "blkuc3" "960,886.31" "1" "1" "180")
(command "_insert" "blkuc3" "960,887.05" "1" "1" "0")
(command "_insert" "blkuc3" "960,886.68" "1" "1" "180")
(command "_insert" "blkuc3" "960,887.42" "1" "1" "0")
(command "_insert" "blkuc3" "960,887.05" "1" "1" "180")
(command "_insert" "blkuc3" "960,887.79" "1" "1" "0")
(command "_insert" "blkuc3" "960,887.42" "1" "1" "180")
(command "_insert" "blkuc3" "960,888.16" "1" "1" "0")
(command "_insert" "blkuc3" "960,887.79" "1" "1" "180")
(command "_insert" "blkuc3" "960,888.53" "1" "1" "0")
(command "_insert" "blkuc3" "960,888.16" "1" "1" "180")
(command "_insert" "blkuc3" "960,888.9" "1" "1" "0")
(command "_insert" "blkuc3" "960,888.53" "1" "1" "180")
(command "_insert" "blkuc3" "960,889.27" "1" "1" "0")
(command "_insert" "blkuc3" "960,888.9" "1" "1" "180")
(command "_insert" "blkuc3" "960,889.64" "1" "1" "0")
(command "_insert" "blkuc3" "960,889.27" "1" "1" "180")
(command "_insert" "blkuc3" "960,890.01" "1" "1" "0")
(command "_insert" "blkuc3" "960,889.64" "1" "1" "180")
(command "_insert" "blkuc3" "960,890.38" "1" "1" "0")
(command "_insert" "blkuc3" "960,890.01" "1" "1" "180")
(command "_insert" "blkuc3" "960,890.75" "1" "1" "0")
(command "_insert" "blkuc3" "960,890.38" "1" "1" "180")
(command "_insert" "blkuc3" "960,891.12" "1" "1" "0")
(command "_insert" "blkuc3" "960,890.75" "1" "1" "180")
(command "_insert" "blkuc3" "960,891.49" "1" "1" "0")
(command "_insert" "blkuc3" "960,891.12" "1" "1" "180")
(command "_insert" "blkuc3" "960,891.86" "1" "1" "0")
(command "_insert" "blkuc3" "960,891.49" "1" "1" "180")
(command "_insert" "blkuc3" "960,892.23" "1" "1" "0")
(command "_insert" "blkuc3" "960,891.86" "1" "1" "180")
(command "_insert" "blkuc3" "960,892.6" "1" "1" "0")
(command "_insert" "blkuc3" "960,892.23" "1" "1" "180")
(command "_insert" "blkuc3" "960,892.97" "1" "1" "0")
(command "_insert" "blkuc3" "960,892.6" "1" "1" "180")
(command "_insert" "blkuc3" "960,893.34" "1" "1" "0")
(command "_insert" "blkuc3" "960,892.97" "1" "1" "180")
(command "_insert" "blkuc3" "960,893.71" "1" "1" "0")
(command "_insert" "blkuc3" "960,893.34" "1" "1" "180")
(command "_insert" "blkuc3" "960,894.08" "1" "1" "0")
(command "_insert" "blkuc3" "960,893.71" "1" "1" "180")
(command "_insert" "blkuc3" "960,894.45" "1" "1" "0")
(command "_insert" "blkuc3" "960,894.08" "1" "1" "180")
(command "_insert" "blkuc3" "960,894.82" "1" "1" "0")
(command "_insert" "blkuc3" "960,894.45" "1" "1" "180")
(command "_insert" "blkuc3" "960,895.19" "1" "1" "0")
(command "_insert" "blkuc3" "960,894.82" "1" "1" "180")
(command "_insert" "blkuc3" "960,895.56" "1" "1" "0")
(command "_insert" "blkuc3" "960,895.19" "1" "1" "180")
(command "_insert" "blkuc3" "960,895.93" "1" "1" "0")
(command "_insert" "blkuc3" "960,895.56" "1" "1" "180")
(command "_insert" "blkuc3" "960,896.3" "1" "1" "0")
(command "_insert" "blkuc3" "960,895.93" "1" "1" "180")
(command "_insert" "blkuc3" "960,896.67" "1" "1" "0")
(command "_insert" "blkuc3" "960,896.3" "1" "1" "180")
(command "_insert" "blkuc3" "960,897.04" "1" "1" "0")
(command "_insert" "blkuc3" "960,896.67" "1" "1" "180")
(command "_insert" "blkuc3" "960,897.41" "1" "1" "0")
(command "_insert" "blkuc3" "960,897.04" "1" "1" "180")
(command "_insert" "blkuc3" "960,897.78" "1" "1" "0")
(command "_insert" "blkuc3" "960,897.41" "1" "1" "180")
(command "_insert" "blkuc3" "960,898.15" "1" "1" "0")
(command "_insert" "blkuc3" "960,897.78" "1" "1" "180")
(command "_insert" "blkuc3" "960,898.52" "1" "1" "0")
(command "_insert" "blkuc3" "960,898.15" "1" "1" "180")
(command "_insert" "blkuc3" "960,898.89" "1" "1" "0")
(command "_insert" "blkuc3" "960,898.52" "1" "1" "180")
(command "_insert" "blkuc3" "960,899.26" "1" "1" "0")
(command "_insert" "blkuc3" "960,898.89" "1" "1" "180")
(command "_insert" "blkuc3" "960,899.63" "1" "1" "0")
(command "_insert" "blkuc3" "960,899.26" "1" "1" "180")
(command "_insert" "blkuc3" "960,900" "1" "1" "0")
(command "_insert" "blkuc3" "960,899.63" "1" "1" "180")
(command "_insert" "blkuc3" "960,900.37" "1" "1" "0")
(command "_insert" "blkuc3" "960,900" "1" "1" "180")
(command "_insert" "blkuc3" "960,900.74" "1" "1" "0")
(command "_insert" "blkuc3" "960,900.37" "1" "1" "180")
(command "_insert" "blkuc3" "960,901.11" "1" "1" "0")
(command "_insert" "blkuc3" "960,900.74" "1" "1" "180")
(command "_insert" "blkuc3" "960,901.48" "1" "1" "0")
(command "_insert" "blkuc3" "960,901.11" "1" "1" "180")
(command "_insert" "blkuc3" "960,901.85" "1" "1" "0")
(command "_insert" "blkuc3" "960,901.48" "1" "1" "180")
(command "_insert" "blkuc3" "960,902.22" "1" "1" "0")
(command "_insert" "blkuc3" "960,901.85" "1" "1" "180")
(command "_insert" "blkuc3" "960,902.59" "1" "1" "0")
(command "_insert" "blkuc3" "960,902.22" "1" "1" "180")
(command "_insert" "blkuc3" "960,902.96" "1" "1" "0")
(command "_insert" "blkuc3" "960,902.59" "1" "1" "180")
(command "_insert" "blkuc3" "960,903.33" "1" "1" "0")
(command "_insert" "blkuc3" "960,902.96" "1" "1" "180")
(command "_insert" "blkuc3" "960,903.7" "1" "1" "0")
(command "_insert" "blkuc3" "960,903.33" "1" "1" "180")
(command "_insert" "blkuc3" "960,904.07" "1" "1" "0")
(command "_insert" "blkuc3" "960,903.7" "1" "1" "180")
(command "_insert" "blkuc3" "960,904.44" "1" "1" "0")
(command "_insert" "blkuc3" "960,904.07" "1" "1" "180")
(command "_insert" "blkuc3" "960,904.81" "1" "1" "0")
(command "_insert" "blkuc3" "960,904.44" "1" "1" "180")
(command "_insert" "blkuc3" "960,905.18" "1" "1" "0")
(command "_insert" "blkuc3" "960,904.81" "1" "1" "180")
(command "_insert" "blkuc3" "960,905.55" "1" "1" "0")
(command "_insert" "blkuc3" "960,905.18" "1" "1" "180")
(command "_insert" "blkuc3" "960,905.92" "1" "1" "0")
(command "_insert" "blkuc3" "960,905.55" "1" "1" "180")
(command "_insert" "blkuc3" "960,906.29" "1" "1" "0")
(command "_insert" "blkuc3" "960,905.92" "1" "1" "180")
(command "_insert" "blkuc3" "960,906.66" "1" "1" "0")
(command "_insert" "blkuc3" "960,906.29" "1" "1" "180")
(command "_insert" "blkuc3" "960,907.03" "1" "1" "0")
(command "_insert" "blkuc3" "960,906.66" "1" "1" "180")
(command "_insert" "blkuc3" "960,907.4" "1" "1" "0")
(command "_insert" "blkuc3" "960,907.03" "1" "1" "180")
(command "_insert" "blkuc3" "960,907.77" "1" "1" "0")
(command "_insert" "blkuc3" "960,907.4" "1" "1" "180")
(command "_insert" "blkuc3" "960,908.14" "1" "1" "0")
(command "_insert" "blkuc3" "960,907.77" "1" "1" "180")
(command "_insert" "blkuc3" "960,908.51" "1" "1" "0")
(command "_insert" "blkuc3" "960,908.14" "1" "1" "180")
(command "_insert" "blkuc3" "960,908.88" "1" "1" "0")
(command "_insert" "blkuc3" "960,908.51" "1" "1" "180")
(command "_insert" "blkuc3" "960,909.25" "1" "1" "0")
(command "_insert" "blkuc3" "960,908.88" "1" "1" "180")
(command "_insert" "blkuc3" "960,909.62" "1" "1" "0")
(command "_insert" "blkuc3" "960,909.25" "1" "1" "180")
(command "_insert" "blkuc3" "960,909.99" "1" "1" "0")
(command "_insert" "blkuc3" "960,909.62" "1" "1" "180")
(command "_insert" "blkuc3" "960,910.36" "1" "1" "0")
(command "_insert" "blkuc3" "960,909.99" "1" "1" "180")
(command "_insert" "blkuc3" "960,910.73" "1" "1" "0")
(command "_insert" "blkuc3" "960,910.36" "1" "1" "180")
(command "_insert" "blkuc3" "960,911.1" "1" "1" "0")
(command "_insert" "blkuc3" "960,910.73" "1" "1" "180")
(command "_insert" "blkuc3" "960,911.47" "1" "1" "0")
(command "_insert" "blkuc3" "960,911.1" "1" "1" "180")
(command "_insert" "blkuc3" "960,911.84" "1" "1" "0")
(command "_insert" "blkuc3" "960,911.47" "1" "1" "180")
(command "_insert" "blkuc3" "960,912.21" "1" "1" "0")
(command "_insert" "blkuc3" "960,911.84" "1" "1" "180")
(command "_insert" "blkuc3" "960,912.58" "1" "1" "0")
(command "_insert" "blkuc3" "960,912.21" "1" "1" "180")
(command "_insert" "blkuc3" "960,912.95" "1" "1" "0")
(command "_insert" "blkuc3" "960,912.58" "1" "1" "180")
(command "_insert" "blkuc3" "960,913.32" "1" "1" "0")
(command "_insert" "blkuc3" "960,912.95" "1" "1" "180")
(command "_insert" "blkuc3" "960,913.69" "1" "1" "0")
(command "_insert" "blkuc3" "960,913.32" "1" "1" "180")
(command "_insert" "blkuc3" "960,914.06" "1" "1" "0")
(command "_insert" "blkuc3" "960,913.69" "1" "1" "180")
(command "_insert" "blkuc3" "960,914.43" "1" "1" "0")
(command "_insert" "blkuc3" "960,914.06" "1" "1" "180")
(command "_insert" "blkuc3" "960,914.8" "1" "1" "0")
(command "_insert" "blkuc3" "960,914.43" "1" "1" "180")
(command "_insert" "blkuc3" "960,915.17" "1" "1" "0")
(command "_insert" "blkuc3" "960,914.8" "1" "1" "180")
(command "_insert" "blkuc3" "960,915.54" "1" "1" "0")
(command "_insert" "blkuc3" "960,915.17" "1" "1" "180")
(command "_insert" "blkuc3" "960,915.91" "1" "1" "0")
(command "_insert" "blkuc3" "960,915.54" "1" "1" "180")
(command "_insert" "blkuc3" "960,916.28" "1" "1" "0")
(command "_insert" "blkuc3" "960,915.91" "1" "1" "180")
(command "_insert" "blkuc3" "960,916.65" "1" "1" "0")
(command "_insert" "blkuc3" "960,916.28" "1" "1" "180")
(command "_insert" "blkuc3" "960,917.02" "1" "1" "0")
(command "_insert" "blkuc3" "960,916.65" "1" "1" "180")
(command "_insert" "blkuc3" "960,917.39" "1" "1" "0")
(command "_insert" "blkuc3" "960,917.02" "1" "1" "180")
(command "_insert" "blkuc3" "960,917.76" "1" "1" "0")
(command "_insert" "blkuc3" "960,917.39" "1" "1" "180")
(command "_insert" "blkuc3" "960,918.13" "1" "1" "0")
(command "_insert" "blkuc3" "960,917.76" "1" "1" "180")
(command "_insert" "blkuc3" "960,918.5" "1" "1" "0")
(command "_insert" "blkuc3" "960,918.13" "1" "1" "180")
(command "_insert" "blkuc3" "960,918.87" "1" "1" "0")
(command "_insert" "blkuc3" "960,918.5" "1" "1" "180")
(command "_insert" "blkuc3" "960,919.24" "1" "1" "0")
(command "_insert" "blkuc3" "960,918.87" "1" "1" "180")
(command "_insert" "blkuc3" "960,919.61" "1" "1" "0")
(command "_insert" "blkuc3" "960,919.24" "1" "1" "180")
(command "_insert" "blkuc3" "960,919.98" "1" "1" "0")
(command "_insert" "blkuc3" "960,919.61" "1" "1" "180")
(command "_insert" "blkuc3" "960,920.35" "1" "1" "0")
(command "_insert" "blkuc3" "960,919.98" "1" "1" "180")
(command "_insert" "blkuc3" "960,920.72" "1" "1" "0")
(command "_insert" "blkuc3" "960,920.35" "1" "1" "180")
(command "_insert" "blkuc3" "960,921.09" "1" "1" "0")
(command "_insert" "blkuc3" "960,920.72" "1" "1" "180")
(command "_insert" "blkuc3" "960,921.46" "1" "1" "0")
(command "_insert" "blkuc3" "960,921.09" "1" "1" "180")
(command "_insert" "blkuc3" "960,921.83" "1" "1" "0")
(command "_insert" "blkuc3" "960,921.46" "1" "1" "180")
(command "_insert" "blkuc3" "960,922.2" "1" "1" "0")
(command "_insert" "blkuc3" "960,921.83" "1" "1" "180")
(command "_insert" "blkuc3" "960,922.57" "1" "1" "0")
(command "_insert" "blkuc3" "960,922.2" "1" "1" "180")
(command "_insert" "blkuc3" "960,922.94" "1" "1" "0")
(command "_insert" "blkuc3" "960,922.57" "1" "1" "180")
(command "_insert" "blkuc3" "960,923.31" "1" "1" "0")
(command "_insert" "blkuc3" "960,922.94" "1" "1" "180")
(command "_insert" "blkuc3" "960,923.68" "1" "1" "0")
(command "_insert" "blkuc3" "960,923.31" "1" "1" "180")
(command "_insert" "blkuc3" "960,924.05" "1" "1" "0")
(command "_insert" "blkuc3" "960,923.68" "1" "1" "180")
(command "_insert" "blkuc3" "960,924.42" "1" "1" "0")
(command "_insert" "blkuc3" "960,924.05" "1" "1" "180")
(command "_insert" "blkuc3" "960,924.79" "1" "1" "0")
(command "_insert" "blkuc3" "960,924.42" "1" "1" "180")
(command "_insert" "blkuc3" "960,925.16" "1" "1" "0")
(command "_insert" "blkuc3" "960,924.79" "1" "1" "180")
(command "_insert" "blkuc3" "960,925.53" "1" "1" "0")
(command "_insert" "blkuc3" "960,925.16" "1" "1" "180")
(command "_insert" "blkuc3" "960,925.9" "1" "1" "0")
(command "_insert" "blkuc3" "960,925.53" "1" "1" "180")
(command "_insert" "blkuc3" "960,926.27" "1" "1" "0")
(command "_insert" "blkuc3" "960,925.9" "1" "1" "180")
(command "_insert" "blkuc3" "960,926.64" "1" "1" "0")
(command "_insert" "blkuc3" "960,926.27" "1" "1" "180")
(command "_insert" "blkuc3" "960,927.01" "1" "1" "0")
(command "_insert" "blkuc3" "960,926.64" "1" "1" "180")
(command "_insert" "blkuc3" "960,927.38" "1" "1" "0")
(command "_insert" "blkuc3" "960,927.01" "1" "1" "180")
(command "_insert" "blkuc3" "960,927.75" "1" "1" "0")
(command "_insert" "blkuc3" "960,927.38" "1" "1" "180")
(command "_layer" "set" "phccover" "")
(command "_rectangle" "958.898,933.3" "961.102,866.7")
(command "_layer" "set" "nitride" "")
(setq phc3 currobj)
(command "_layer" "set" "cover" "")
(command "_rectangle" "958.898,836.7" "961.102,963.3")
(command "_layer" "set" "nitride" "")
(command "_layer" "set" "text" "")
(command "_circle" "957.948,846.7" "0.075")
(command "_circle" "957.573,846.7" "0.15")
(command "_circle" "957.198,846.7" "0.075")
(command "_circle" "956.823,846.7" "0.15")
(command "_circle" "957.948,848.7" "0.075")
(command "_circle" "957.573,848.7" "0.075")
(command "_circle" "957.198,848.7" "0.15")
(command "_circle" "956.823,848.7" "0.15")
(command "_circle" "957.948,850.7" "0.075")
(command "_circle" "957.573,850.7" "0.15")
(command "_circle" "957.198,850.7" "0.15")
(command "_circle" "956.823,850.7" "0.15")
(command "_circle" "957.948,852.7" "0.075")
(command "_circle" "957.573,852.7" "0.075")
(command "_circle" "957.198,852.7" "0.075")
(command "_circle" "956.823,852.7" "0.075")
(command "_circle" "956.448,852.7" "0.15")
(command "_circle" "957.948,854.7" "0.075")
(command "_circle" "957.573,854.7" "0.15")
(command "_circle" "957.198,854.7" "0.075")
(command "_circle" "956.823,854.7" "0.075")
(command "_circle" "956.448,854.7" "0.15")
(command "_circle" "957.948,856.7" "0.075")
(command "_circle" "957.573,856.7" "0.075")
(command "_circle" "957.198,856.7" "0.15")
(command "_circle" "956.823,856.7" "0.075")
(command "_circle" "956.448,856.7" "0.15")
(command "_circle" "957.948,858.7" "0.075")
(command "_circle" "957.573,858.7" "0.15")
(command "_circle" "957.198,858.7" "0.15")
(command "_circle" "956.823,858.7" "0.075")
(command "_circle" "956.448,858.7" "0.15")
(command "_circle" "957.948,860.7" "0.075")
(command "_circle" "957.573,860.7" "0.075")
(command "_circle" "957.198,860.7" "0.075")
(command "_circle" "956.823,860.7" "0.15")
(command "_circle" "956.448,860.7" "0.15")
(command "_circle" "957.948,862.7" "0.075")
(command "_circle" "957.573,862.7" "0.15")
(command "_circle" "957.198,862.7" "0.075")
(command "_circle" "956.823,862.7" "0.15")
(command "_circle" "956.448,862.7" "0.15")
(command "_circle" "957.948,864.7" "0.075")
(command "_circle" "957.573,864.7" "0.075")
(command "_circle" "957.198,864.7" "0.15")
(command "_circle" "956.823,864.7" "0.15")
(command "_circle" "956.448,864.7" "0.15")
(command "_circle" "957.948,866.7" "0.075")
(command "_circle" "957.573,866.7" "0.15")
(command "_circle" "957.198,866.7" "0.15")
(command "_circle" "956.823,866.7" "0.15")
(command "_circle" "956.448,866.7" "0.15")
(command "_circle" "957.948,868.7" "0.075")
(command "_circle" "957.573,868.7" "0.075")
(command "_circle" "957.198,868.7" "0.075")
(command "_circle" "956.823,868.7" "0.075")
(command "_circle" "956.448,868.7" "0.075")
(command "_circle" "956.073,868.7" "0.15")
(command "_circle" "957.948,870.7" "0.075")
(command "_circle" "957.573,870.7" "0.15")
(command "_circle" "957.198,870.7" "0.075")
(command "_circle" "956.823,870.7" "0.075")
(command "_circle" "956.448,870.7" "0.075")
(command "_circle" "956.073,870.7" "0.15")
(command "_circle" "957.948,872.7" "0.075")
(command "_circle" "957.573,872.7" "0.075")
(command "_circle" "957.198,872.7" "0.15")
(command "_circle" "956.823,872.7" "0.075")
(command "_circle" "956.448,872.7" "0.075")
(command "_circle" "956.073,872.7" "0.15")
(command "_circle" "957.948,874.7" "0.075")
(command "_circle" "957.573,874.7" "0.15")
(command "_circle" "957.198,874.7" "0.15")
(command "_circle" "956.823,874.7" "0.075")
(command "_circle" "956.448,874.7" "0.075")
(command "_circle" "956.073,874.7" "0.15")
(command "_circle" "957.948,876.7" "0.075")
(command "_circle" "957.573,876.7" "0.075")
(command "_circle" "957.198,876.7" "0.075")
(command "_circle" "956.823,876.7" "0.15")
(command "_circle" "956.448,876.7" "0.075")
(command "_circle" "956.073,876.7" "0.15")
(command "_circle" "957.948,878.7" "0.075")
(command "_circle" "957.573,878.7" "0.15")
(command "_circle" "957.198,878.7" "0.075")
(command "_circle" "956.823,878.7" "0.15")
(command "_circle" "956.448,878.7" "0.075")
(command "_circle" "956.073,878.7" "0.15")
(command "_circle" "957.948,880.7" "0.075")
(command "_circle" "957.573,880.7" "0.075")
(command "_circle" "957.198,880.7" "0.15")
(command "_circle" "956.823,880.7" "0.15")
(command "_circle" "956.448,880.7" "0.075")
(command "_circle" "956.073,880.7" "0.15")
(command "_circle" "957.948,882.7" "0.075")
(command "_circle" "957.573,882.7" "0.15")
(command "_circle" "957.198,882.7" "0.15")
(command "_circle" "956.823,882.7" "0.15")
(command "_circle" "956.448,882.7" "0.075")
(command "_circle" "956.073,882.7" "0.15")
(command "_circle" "957.948,884.7" "0.075")
(command "_circle" "957.573,884.7" "0.075")
(command "_circle" "957.198,884.7" "0.075")
(command "_circle" "956.823,884.7" "0.075")
(command "_circle" "956.448,884.7" "0.15")
(command "_circle" "956.073,884.7" "0.15")
(command "_circle" "957.948,886.7" "0.075")
(command "_circle" "957.573,886.7" "0.15")
(command "_circle" "957.198,886.7" "0.075")
(command "_circle" "956.823,886.7" "0.075")
(command "_circle" "956.448,886.7" "0.15")
(command "_circle" "956.073,886.7" "0.15")
(command "_circle" "957.948,888.7" "0.075")
(command "_circle" "957.573,888.7" "0.075")
(command "_circle" "957.198,888.7" "0.15")
(command "_circle" "956.823,888.7" "0.075")
(command "_circle" "956.448,888.7" "0.15")
(command "_circle" "956.073,888.7" "0.15")
(command "_circle" "957.948,890.7" "0.075")
(command "_circle" "957.573,890.7" "0.15")
(command "_circle" "957.198,890.7" "0.15")
(command "_circle" "956.823,890.7" "0.075")
(command "_circle" "956.448,890.7" "0.15")
(command "_circle" "956.073,890.7" "0.15")
(command "_circle" "957.948,892.7" "0.075")
(command "_circle" "957.573,892.7" "0.075")
(command "_circle" "957.198,892.7" "0.075")
(command "_circle" "956.823,892.7" "0.15")
(command "_circle" "956.448,892.7" "0.15")
(command "_circle" "956.073,892.7" "0.15")
(command "_circle" "957.948,894.7" "0.075")
(command "_circle" "957.573,894.7" "0.15")
(command "_circle" "957.198,894.7" "0.075")
(command "_circle" "956.823,894.7" "0.15")
(command "_circle" "956.448,894.7" "0.15")
(command "_circle" "956.073,894.7" "0.15")
(command "_circle" "957.948,896.7" "0.075")
(command "_circle" "957.573,896.7" "0.075")
(command "_circle" "957.198,896.7" "0.15")
(command "_circle" "956.823,896.7" "0.15")
(command "_circle" "956.448,896.7" "0.15")
(command "_circle" "956.073,896.7" "0.15")
(command "_circle" "957.948,898.7" "0.075")
(command "_circle" "957.573,898.7" "0.15")
(command "_circle" "957.198,898.7" "0.15")
(command "_circle" "956.823,898.7" "0.15")
(command "_circle" "956.448,898.7" "0.15")
(command "_circle" "956.073,898.7" "0.15")
(command "_circle" "957.948,900.7" "0.075")
(command "_circle" "957.573,900.7" "0.075")
(command "_circle" "957.198,900.7" "0.075")
(command "_circle" "956.823,900.7" "0.075")
(command "_circle" "956.448,900.7" "0.075")
(command "_circle" "956.073,900.7" "0.075")
(command "_circle" "955.698,900.7" "0.15")
(command "_circle" "957.948,902.7" "0.075")
(command "_circle" "957.573,902.7" "0.15")
(command "_circle" "957.198,902.7" "0.075")
(command "_circle" "956.823,902.7" "0.075")
(command "_circle" "956.448,902.7" "0.075")
(command "_circle" "956.073,902.7" "0.075")
(command "_circle" "955.698,902.7" "0.15")
(command "_circle" "957.948,904.7" "0.075")
(command "_circle" "957.573,904.7" "0.075")
(command "_circle" "957.198,904.7" "0.15")
(command "_circle" "956.823,904.7" "0.075")
(command "_circle" "956.448,904.7" "0.075")
(command "_circle" "956.073,904.7" "0.075")
(command "_circle" "955.698,904.7" "0.15")
(command "_circle" "957.948,906.7" "0.075")
(command "_circle" "957.573,906.7" "0.15")
(command "_circle" "957.198,906.7" "0.15")
(command "_circle" "956.823,906.7" "0.075")
(command "_circle" "956.448,906.7" "0.075")
(command "_circle" "956.073,906.7" "0.075")
(command "_circle" "955.698,906.7" "0.15")
(command "_circle" "957.948,908.7" "0.075")
(command "_circle" "957.573,908.7" "0.075")
(command "_circle" "957.198,908.7" "0.075")
(command "_circle" "956.823,908.7" "0.15")
(command "_circle" "956.448,908.7" "0.075")
(command "_circle" "956.073,908.7" "0.075")
(command "_circle" "955.698,908.7" "0.15")
(command "_circle" "957.948,910.7" "0.075")
(command "_circle" "957.573,910.7" "0.15")
(command "_circle" "957.198,910.7" "0.075")
(command "_circle" "956.823,910.7" "0.15")
(command "_circle" "956.448,910.7" "0.075")
(command "_circle" "956.073,910.7" "0.075")
(command "_circle" "955.698,910.7" "0.15")
(command "_circle" "957.948,912.7" "0.075")
(command "_circle" "957.573,912.7" "0.075")
(command "_circle" "957.198,912.7" "0.15")
(command "_circle" "956.823,912.7" "0.15")
(command "_circle" "956.448,912.7" "0.075")
(command "_circle" "956.073,912.7" "0.075")
(command "_circle" "955.698,912.7" "0.15")
(command "_circle" "957.948,914.7" "0.075")
(command "_circle" "957.573,914.7" "0.15")
(command "_circle" "957.198,914.7" "0.15")
(command "_circle" "956.823,914.7" "0.15")
(command "_circle" "956.448,914.7" "0.075")
(command "_circle" "956.073,914.7" "0.075")
(command "_circle" "955.698,914.7" "0.15")
(command "_circle" "957.948,916.7" "0.075")
(command "_circle" "957.573,916.7" "0.075")
(command "_circle" "957.198,916.7" "0.075")
(command "_circle" "956.823,916.7" "0.075")
(command "_circle" "956.448,916.7" "0.15")
(command "_circle" "956.073,916.7" "0.075")
(command "_circle" "955.698,916.7" "0.15")
(command "_circle" "957.948,918.7" "0.075")
(command "_circle" "957.573,918.7" "0.15")
(command "_circle" "957.198,918.7" "0.075")
(command "_circle" "956.823,918.7" "0.075")
(command "_circle" "956.448,918.7" "0.15")
(command "_circle" "956.073,918.7" "0.075")
(command "_circle" "955.698,918.7" "0.15")
(command "_circle" "957.948,920.7" "0.075")
(command "_circle" "957.573,920.7" "0.075")
(command "_circle" "957.198,920.7" "0.15")
(command "_circle" "956.823,920.7" "0.075")
(command "_circle" "956.448,920.7" "0.15")
(command "_circle" "956.073,920.7" "0.075")
(command "_circle" "955.698,920.7" "0.15")
(command "_circle" "957.948,922.7" "0.075")
(command "_circle" "957.573,922.7" "0.15")
(command "_circle" "957.198,922.7" "0.15")
(command "_circle" "956.823,922.7" "0.075")
(command "_circle" "956.448,922.7" "0.15")
(command "_circle" "956.073,922.7" "0.075")
(command "_circle" "955.698,922.7" "0.15")
(command "_circle" "957.948,924.7" "0.075")
(command "_circle" "957.573,924.7" "0.075")
(command "_circle" "957.198,924.7" "0.075")
(command "_circle" "956.823,924.7" "0.15")
(command "_circle" "956.448,924.7" "0.15")
(command "_circle" "956.073,924.7" "0.075")
(command "_circle" "955.698,924.7" "0.15")
(command "_circle" "957.948,926.7" "0.075")
(command "_circle" "957.573,926.7" "0.15")
(command "_circle" "957.198,926.7" "0.075")
(command "_circle" "956.823,926.7" "0.15")
(command "_circle" "956.448,926.7" "0.15")
(command "_circle" "956.073,926.7" "0.075")
(command "_circle" "955.698,926.7" "0.15")
(command "_circle" "957.948,928.7" "0.075")
(command "_circle" "957.573,928.7" "0.075")
(command "_circle" "957.198,928.7" "0.15")
(command "_circle" "956.823,928.7" "0.15")
(command "_circle" "956.448,928.7" "0.15")
(command "_circle" "956.073,928.7" "0.075")
(command "_circle" "955.698,928.7" "0.15")
(command "_circle" "957.948,930.7" "0.075")
(command "_circle" "957.573,930.7" "0.15")
(command "_circle" "957.198,930.7" "0.15")
(command "_circle" "956.823,930.7" "0.15")
(command "_circle" "956.448,930.7" "0.15")
(command "_circle" "956.073,930.7" "0.075")
(command "_circle" "955.698,930.7" "0.15")
(command "_circle" "957.948,932.7" "0.075")
(command "_circle" "957.573,932.7" "0.075")
(command "_circle" "957.198,932.7" "0.075")
(command "_circle" "956.823,932.7" "0.075")
(command "_circle" "956.448,932.7" "0.075")
(command "_circle" "956.073,932.7" "0.15")
(command "_circle" "955.698,932.7" "0.15")
(command "_circle" "957.948,934.7" "0.075")
(command "_circle" "957.573,934.7" "0.15")
(command "_circle" "957.198,934.7" "0.075")
(command "_circle" "956.823,934.7" "0.075")
(command "_circle" "956.448,934.7" "0.075")
(command "_circle" "956.073,934.7" "0.15")
(command "_circle" "955.698,934.7" "0.15")
(command "_circle" "957.948,936.7" "0.075")
(command "_circle" "957.573,936.7" "0.075")
(command "_circle" "957.198,936.7" "0.15")
(command "_circle" "956.823,936.7" "0.075")
(command "_circle" "956.448,936.7" "0.075")
(command "_circle" "956.073,936.7" "0.15")
(command "_circle" "955.698,936.7" "0.15")
(command "_circle" "957.948,938.7" "0.075")
(command "_circle" "957.573,938.7" "0.15")
(command "_circle" "957.198,938.7" "0.15")
(command "_circle" "956.823,938.7" "0.075")
(command "_circle" "956.448,938.7" "0.075")
(command "_circle" "956.073,938.7" "0.15")
(command "_circle" "955.698,938.7" "0.15")
(command "_circle" "957.948,940.7" "0.075")
(command "_circle" "957.573,940.7" "0.075")
(command "_circle" "957.198,940.7" "0.075")
(command "_circle" "956.823,940.7" "0.15")
(command "_circle" "956.448,940.7" "0.075")
(command "_circle" "956.073,940.7" "0.15")
(command "_circle" "955.698,940.7" "0.15")
(command "_circle" "957.948,942.7" "0.075")
(command "_circle" "957.573,942.7" "0.15")
(command "_circle" "957.198,942.7" "0.075")
(command "_circle" "956.823,942.7" "0.15")
(command "_circle" "956.448,942.7" "0.075")
(command "_circle" "956.073,942.7" "0.15")
(command "_circle" "955.698,942.7" "0.15")
(command "_circle" "957.948,944.7" "0.075")
(command "_circle" "957.573,944.7" "0.075")
(command "_circle" "957.198,944.7" "0.15")
(command "_circle" "956.823,944.7" "0.15")
(command "_circle" "956.448,944.7" "0.075")
(command "_circle" "956.073,944.7" "0.15")
(command "_circle" "955.698,944.7" "0.15")
(command "_circle" "957.948,946.7" "0.075")
(command "_circle" "957.573,946.7" "0.15")
(command "_circle" "957.198,946.7" "0.15")
(command "_circle" "956.823,946.7" "0.15")
(command "_circle" "956.448,946.7" "0.075")
(command "_circle" "956.073,946.7" "0.15")
(command "_circle" "955.698,946.7" "0.15")
(command "_circle" "957.948,948.7" "0.075")
(command "_circle" "957.573,948.7" "0.075")
(command "_circle" "957.198,948.7" "0.075")
(command "_circle" "956.823,948.7" "0.075")
(command "_circle" "956.448,948.7" "0.15")
(command "_circle" "956.073,948.7" "0.15")
(command "_circle" "955.698,948.7" "0.15")
(command "_circle" "957.948,950.7" "0.075")
(command "_circle" "957.573,950.7" "0.15")
(command "_circle" "957.198,950.7" "0.075")
(command "_circle" "956.823,950.7" "0.075")
(command "_circle" "956.448,950.7" "0.15")
(command "_circle" "956.073,950.7" "0.15")
(command "_circle" "955.698,950.7" "0.15")
(command "_circle" "957.948,952.7" "0.075")
(command "_circle" "957.573,952.7" "0.075")
(command "_circle" "957.198,952.7" "0.15")
(command "_circle" "956.823,952.7" "0.075")
(command "_circle" "956.448,952.7" "0.15")
(command "_circle" "956.073,952.7" "0.15")
(command "_circle" "955.698,952.7" "0.15")
(command "_circle" "957.948,954.7" "0.075")
(command "_circle" "957.573,954.7" "0.15")
(command "_circle" "957.198,954.7" "0.15")
(command "_circle" "956.823,954.7" "0.075")
(command "_circle" "956.448,954.7" "0.15")
(command "_circle" "956.073,954.7" "0.15")
(command "_circle" "955.698,954.7" "0.15")
(command "_circle" "957.948,956.7" "0.075")
(command "_circle" "957.573,956.7" "0.075")
(command "_circle" "957.198,956.7" "0.075")
(command "_circle" "956.823,956.7" "0.15")
(command "_circle" "956.448,956.7" "0.15")
(command "_circle" "956.073,956.7" "0.15")
(command "_circle" "955.698,956.7" "0.15")
(command "_circle" "957.948,958.7" "0.075")
(command "_circle" "957.573,958.7" "0.15")
(command "_circle" "957.198,958.7" "0.075")
(command "_circle" "956.823,958.7" "0.15")
(command "_circle" "956.448,958.7" "0.15")
(command "_circle" "956.073,958.7" "0.15")
(command "_circle" "955.698,958.7" "0.15")
(command "_circle" "957.948,960.7" "0.075")
(command "_circle" "957.573,960.7" "0.075")
(command "_circle" "957.198,960.7" "0.15")
(command "_circle" "956.823,960.7" "0.15")
(command "_circle" "956.448,960.7" "0.15")
(command "_circle" "956.073,960.7" "0.15")
(command "_circle" "955.698,960.7" "0.15")
(command "_circle" "957.948,962.7" "0.075")
(command "_circle" "957.573,962.7" "0.15")
(command "_circle" "957.198,962.7" "0.15")
(command "_circle" "956.823,962.7" "0.15")
(command "_circle" "956.448,962.7" "0.15")
(command "_circle" "956.073,962.7" "0.15")
(command "_circle" "955.698,962.7" "0.15")
(command "_layer" "set" "nitride" "")
(command "_layer" "set" "text" "")
(command-s "_text" "946.898,963.3" "2" "-90" "a = 370 nm" )
(sssetfirst nil (ssget "_L"))
(if (not (numberp (vl-string-search "Mac" (getvar "platform")))) (c:txtexp))
(command "_layer" "set" "nitride" "")
(command "_layer" "set" "text" "")
(command-s "_text" "943.898,963.3" "2" "-90" "gap = 250 nm" )
(sssetfirst nil (ssget "_L"))
(if (not (numberp (vl-string-search "Mac" (getvar "platform")))) (c:txtexp))
(command "_layer" "set" "nitride" "")
(command "_layer" "set" "text" "")
(command-s "_text" "940.898,963.3" "2" "-90" "amplitude = 137 nm" )
(sssetfirst nil (ssget "_L"))
(if (not (numberp (vl-string-search "Mac" (getvar "platform")))) (c:txtexp))
(command "_layer" "set" "nitride" "")
(command "_layer" "set" "text" "")
(command-s "_text" "937.898,963.3" "2" "-90" "start width = 280 nm" )
(sssetfirst nil (ssget "_L"))
(if (not (numberp (vl-string-search "Mac" (getvar "platform")))) (c:txtexp))
(command "_layer" "set" "nitride" "")
(command "_layer" "set" "text" "")
(command-s "_text" "934.898,963.3" "2" "-90" "width = 289 nm" )
(sssetfirst nil (ssget "_L"))
(if (not (numberp (vl-string-search "Mac" (getvar "platform")))) (c:txtexp))
(command "_layer" "set" "nitride" "")
(command "_layer" "set" "text" "")
(command-s "_text" "931.898,963.3" "2" "-90" "taper: 15" )
(sssetfirst nil (ssget "_L"))
(if (not (numberp (vl-string-search "Mac" (getvar "platform")))) (c:txtexp))
(command "_layer" "set" "nitride" "")
(command "_layer" "set" "text" "")
(command-s "_text" "928.898,963.3" "2" "-90" "nominal: 150" )
(sssetfirst nil (ssget "_L"))
(if (not (numberp (vl-string-search "Mac" (getvar "platform")))) (c:txtexp))
(command "_layer" "set" "nitride" "")
(command "_layer" "set" "indicators" "")
(setq coords (list 
(list 880.415 940) 
(list 880.415 920) 
(list 860.415 900) 
(list 880.415 880) 
(list 880.415 860) 
(list 880.415 900) 
(list 880.415 887.0711) 
(list 867.4861 900) 
(list 880.415 912.9289) 
(list 880.415 900)))
(apply 'command (append '("pline") coords '("c")))
(command "._fillet" "radius" "1" "._fillet" "P" (entlast))
(setq coords (list 
(list 1039.585 940) 
(list 1039.585 920) 
(list 1059.585 900) 
(list 1039.585 880) 
(list 1039.585 860) 
(list 1039.585 900) 
(list 1039.585 887.0711) 
(list 1052.5139 900) 
(list 1039.585 912.9289) 
(list 1039.585 900)))
(apply 'command (append '("pline") coords '("c")))
(command "._fillet" "radius" "1" "._fillet" "P" (entlast))
(command "_layer" "set" "holes" "")
(command "_circle" "878.0629,914.1124" "0.5")
(command "_circle" "875.7109,911.7603" "0.5")
(command "_circle" "873.3588,909.4083" "0.5")
(command "_circle" "871.0067,907.0562" "0.5")
(command "_circle" "868.6547,904.7041" "0.5")
(command "_circle" "866.3026,902.3521" "0.5")
(command "_circle" "863.9505,900" "0.5")
(command "_circle" "866.3026,897.6479" "0.5")
(command "_circle" "868.6547,895.2959" "0.5")
(command "_circle" "871.0067,892.9438" "0.5")
(command "_circle" "873.3588,890.5917" "0.5")
(command "_circle" "875.7109,888.2397" "0.5")
(command "_circle" "878.0629,885.8876" "0.5")
(command "_circle" "1041.9371,914.1124" "0.5")
(command "_circle" "1044.2891,911.7603" "0.5")
(command "_circle" "1046.6412,909.4083" "0.5")
(command "_circle" "1048.9933,907.0562" "0.5")
(command "_circle" "1051.3453,904.7041" "0.5")
(command "_circle" "1053.6974,902.3521" "0.5")
(command "_circle" "1056.0495,900" "0.5")
(command "_circle" "1053.6974,897.6479" "0.5")
(command "_circle" "1051.3453,895.2959" "0.5")
(command "_circle" "1048.9933,892.9438" "0.5")
(command "_circle" "1046.6412,890.5917" "0.5")
(command "_circle" "1044.2891,888.2397" "0.5")
(command "_circle" "1041.9371,885.8876" "0.5")
(command "_layer" "set" "nitride" "")
(command "_block" "blkcoupler3" "960,900" coupler3 "")
(command "_insert" "blkcoupler3" "960,900" "1" "1" "0")
(command "_insert" "blkcoupler3" "960,900" "1" "1" "180")
(command "_block" "blksinglenanobeam3" "960,900" singlenanobeam3 "")
(command "_insert" "blksinglenanobeam3" "960,900" "1" "1" "0")
(command "_insert" "blksinglenanobeam3" "960,900" "1" "1" "180")
(command "_block" "blkanglednodearray3" "960,900" anglednodearray3 "")
(command "_insert" "blkanglednodearray3" "960,900" "1" "1" "0")
(command "_insert" "blkanglednodearray3" "960,900" "1" "1" "180")
(command "_block" "blkcooledsinglenanobeam3" "960,900" cooledsinglenanobeam3 "")
(command "_insert" "blkcooledsinglenanobeam3" "960,900" "1" "1" "0")
(command "_insert" "blkcooledsinglenanobeam3" "960,900" "1" "1" "180")
(command "_block" "blkyjunction3" "960,900" yjunction3 "")
(command "_insert" "blkyjunction3" "960,900" "1" "1" "0")
(command "_insert" "blkyjunction3" "960,900" "1" "1" "180")
; DRAWING BULGING VEE GROOVE
(command "_layer" "set" "vgroove" "")
(setq coords (list 
(list 885.415 -605) 
(list 885.415 0) 
(list 885.415 0) 
(list 885.415 1800) 
(list 885.415 1800) 
(list 885.415 2405) 
(list 1034.585 2405) 
(list 1034.585 1800) 
(list 1034.585 1800) 
(list 1034.585 0) 
(list 1034.585 0) 
(list 1034.585 -605)))
(apply 'command (append '("pline") coords '("c")))
(command "._fillet" "radius" "0" "._fillet" "P" (entlast))
(command "_layer" "set" "window" "")
(command "_rectangle" "885.415,-1935" "1034.585,-600")
(command "_rectangle" "885.415,2400" "1034.585,5300")
(command "_layer" "set" "grid" "")
(command "_rectangle" "886.415,-1934" "909.9433,-1909.2133")
(command "_array" "last" "" "R" "75" "3" "25.7867" "24.5283")
(command "_rectangle" "961,-1934" "984.5283,-1909.2133")
(command "_array" "last" "" "R" "75" "3" "25.7867" "24.5283")
(command "_rectangle" "886.415,1" "909.9433,25.7")
(command "_array" "last" "" "R" "70" "3" "25.7" "24.5283")
(command "_rectangle" "961,1" "984.5283,25.7")
(command "_array" "last" "" "R" "70" "3" "25.7" "24.5283")
(command "_rectangle" "886.415,1801" "909.9433,1825.9185")
(command "_array" "last" "" "R" "135" "3" "25.9185" "24.5283")
(command "_rectangle" "961,1801" "984.5283,1825.9185")
(command "_array" "last" "" "R" "135" "3" "25.9185" "24.5283")
(command "_layer" "set" "vgrooveFDA" "")
(command "_rectangle" "1034.585,-2233" "885.415,-1933")
(command "_layer" "set" "nitride" "")
(command "_layer" "set" "holes" "")
(command "_circle" "1037.085,331.5" "0.5")
(command "_array" "last" "" "R" "379" "1" "3" "2.5")
(command "_circle" "882.915,331.5" "0.5")
(command "_array" "last" "" "R" "379" "1" "3" "-2.5")
(command "_layer" "set" "nitride" "")
(command "_layer" "set" "window" "")
(command "_layer" "set" "window" "")
(command "_rectangle" "1039.585,0" "1200.415,1800")
(command "._fillet" "radius" "20" "._fillet" "P" (entlast))
(command "_layer" "set" "grid" "")
(command "_rectangle" "1040.585,1" "1062.4179,25.7")
(command "_array" "last" "" "R" "70" "7" "25.7" "22.8329")
(command "_layer" "set" "nitride" "")
; DRAWING REGION LAYER
(command "_layer" "set" "regionLayer3" "")
(command "_rectangle" "880,-460" "1040,2260")
(command "_layer" "set" "nitride" "")
(setq coupler3 nil)
(setq singlenanobeam3 nil)
(setq anglednodearray3 nil)
(setq cooledsinglenanobeam3 nil)
(setq yjunction3 nil)
; DEVICE #4
(command "_layer" "set" "window" "")
(command "_circle" "1192.915,-415" "5")
(command "_circle" "1192.915,-402.5" "5")
(command "_circle" "1192.915,-390" "5")
(command "_circle" "1192.915,-377.5" "5")
(command "_layer" "set" "nitride" "")
(setq currobj nil)
(setq currobj (ssadd))
; DRAWING COUPLER
(setq coords (list 
(list 1280.0575 -415) 
(list 1280.0575 -413) 
(list 1353.585 -413) 
(list 1353.585 -413) 
(list 1353.9677 -413.0761) 
(list 1354.2921 -413.2929) 
(list 1354.5089 -413.6173) 
(list 1354.585 -414) 
(list 1354.585 -411.8) 
(list 1354.585 -411.8) 
(list 1354.5089 -412.1827) 
(list 1354.2921 -412.5071) 
(list 1353.9677 -412.7239) 
(list 1353.585 -412.8) 
(list 1280.0575 -412.8) 
(list 1280.0575 -410.8) 
(list 1279.9425 -410.8) 
(list 1279.9425 -412.8) 
(list 1206.415 -412.8) 
(list 1206.0323 -412.7239) 
(list 1205.7079 -412.5071) 
(list 1205.4911 -412.1827) 
(list 1205.415 -411.8) 
(list 1205.415 -411.8) 
(list 1205.415 -414) 
(list 1205.4911 -413.6173) 
(list 1205.7079 -413.2929) 
(list 1206.0323 -413.0761) 
(list 1206.415 -413) 
(list 1206.415 -413) 
(list 1279.9425 -413) 
(list 1279.9425 -415)))
(apply 'command (append '("pline") coords '("c")))
(setq currobj (ssadd (entlast) currobj))
(command "._fillet" "radius" "0.3" "._fillet" "P" (entlast))
(command "_layer" "set" "holes" "")
(command "_circle" "1280,-412.9" "0.113")
(setq currobj (ssadd (entlast) currobj))
(command "_layer" "set" "nitride" "")
(command "_layer" "set" "text" "")
(command "_circle" "1279.2,-415" "0.075")
(command "_circle" "1279.2,-414.7" "0.075")
(command "_circle" "1279.2,-414.4" "0.075")
(command "_circle" "1278.9,-415" "0.075")
(command "_circle" "1278.9,-414.7" "0.075")
(command "_circle" "1278.9,-414.4" "0.075")
(command "_circle" "1278.6,-415" "0.075")
(command "_circle" "1278.6,-414.7" "0.075")
(command "_circle" "1278.6,-414.4" "0.075")
(command "_layer" "set" "nitride" "")
(command "_layer" "set" "prebias" "")
(command "_rectangle" "1205.415,-414" "1354.585,-411.8")
(setq currobj (ssadd (entlast) currobj))
(command "_rectangle" "1279.9425,-415" "1280.0575,-410.8")
(setq currobj (ssadd (entlast) currobj))
(command "_layer" "set" "nitride" "")
(setq coupler4 currobj)
(setq currobj nil)
(setq currobj (ssadd))
; DRAWING SINGLE NANOBEAM
(setq coords (list 
(list 1280.0575 -410.8) 
(list 1280.0575 -409.1417) 
(list 1280.0575 -407.4833) 
(list 1280.0575 -405.825) 
(list 1280.0575 -404.1667) 
(list 1280.0575 -402.5083) 
(list 1280.0575 -400.85) 
(list 1280.0575 -399.1917) 
(list 1280.0575 -397.5333) 
(list 1280.0576 -395.875) 
(list 1280.0576 -394.2167) 
(list 1280.0576 -392.5583) 
(list 1280.0576 -390.9) 
(list 1280.0577 -389.2417) 
(list 1280.0577 -387.5833) 
(list 1280.0577 -385.925) 
(list 1280.0578 -384.2667) 
(list 1280.0579 -382.6083) 
(list 1280.0579 -380.95) 
(list 1280.058 -379.2917) 
(list 1280.0581 -377.6333) 
(list 1280.0582 -375.975) 
(list 1280.0583 -374.3167) 
(list 1280.0584 -372.6583) 
(list 1280.0585 -371) 
(list 1280.0587 -369.3417) 
(list 1280.0588 -367.6833) 
(list 1280.059 -366.025) 
(list 1280.0591 -364.3667) 
(list 1280.0593 -362.7083) 
(list 1280.0595 -361.05) 
(list 1280.0597 -359.3917) 
(list 1280.0599 -357.7333) 
(list 1280.0602 -356.075) 
(list 1280.0604 -354.4167) 
(list 1280.0607 -352.7583) 
(list 1280.0609 -351.1) 
(list 1280.0612 -349.4417) 
(list 1280.0615 -347.7833) 
(list 1280.0619 -346.125) 
(list 1280.0622 -344.4667) 
(list 1280.0626 -342.8083) 
(list 1280.063 -341.15) 
(list 1280.0634 -339.4917) 
(list 1280.0638 -337.8333) 
(list 1280.0642 -336.175) 
(list 1280.0647 -334.5167) 
(list 1280.0652 -332.8583) 
(list 1280.0657 -331.2) 
(list 1280.0662 -329.5417) 
(list 1280.0667 -327.8833) 
(list 1280.0673 -326.225) 
(list 1280.0679 -324.5667) 
(list 1280.0685 -322.9083) 
(list 1280.0691 -321.25) 
(list 1280.0698 -319.5917) 
(list 1280.0705 -317.9333) 
(list 1280.0712 -316.275) 
(list 1280.0719 -314.6167) 
(list 1280.0727 -312.9583) 
(list 1280.0734 -311.3) 
(list 1280.0742 -309.6417) 
(list 1280.0751 -307.9833) 
(list 1280.0759 -306.325) 
(list 1280.0768 -304.6667) 
(list 1280.0778 -303.0083) 
(list 1280.0787 -301.35) 
(list 1280.0797 -299.6917) 
(list 1280.0807 -298.0333) 
(list 1280.0817 -296.375) 
(list 1280.0828 -294.7167) 
(list 1280.0839 -293.0583) 
(list 1280.085 -291.4) 
(list 1280.0862 -289.7417) 
(list 1280.0874 -288.0833) 
(list 1280.0886 -286.425) 
(list 1280.0899 -284.7667) 
(list 1280.0912 -283.1083) 
(list 1280.0925 -281.45) 
(list 1280.0939 -279.7917) 
(list 1280.0953 -278.1333) 
(list 1280.0967 -276.475) 
(list 1280.0982 -274.8167) 
(list 1280.0997 -273.1583) 
(list 1280.1012 -271.5) 
(list 1280.1028 -269.8417) 
(list 1280.1044 -268.1833) 
(list 1280.1061 -266.525) 
(list 1280.1078 -264.8667) 
(list 1280.1095 -263.2083) 
(list 1280.1113 -261.55) 
(list 1280.1131 -259.8917) 
(list 1280.115 -258.2333) 
(list 1280.1168 -256.575) 
(list 1280.1188 -254.9167) 
(list 1280.1208 -253.2583) 
(list 1280.1228 -251.6) 
(list 1280.1248 -249.9417) 
(list 1280.1269 -248.2833) 
(list 1280.1291 -246.625) 
(list 1280.1313 -244.9667) 
(list 1280.1335 -243.3083) 
(list 1280.1358 -241.65) 
(list 1280.1381 -239.9917) 
(list 1280.1405 -238.3333) 
(list 1280.1429 -236.675) 
(list 1280.1454 -235.0167) 
(list 1280.1479 -233.3583) 
(list 1280.1504 -231.7) 
(list 1280.1531 -230.0417) 
(list 1280.1557 -228.3833) 
(list 1280.1584 -226.725) 
(list 1280.1612 -225.0667) 
(list 1280.164 -223.4083) 
(list 1280.1668 -221.75) 
(list 1280.1697 -220.0917) 
(list 1280.1727 -218.4333) 
(list 1280.1757 -216.775) 
(list 1280.1787 -215.1167) 
(list 1280.1818 -213.4583) 
(list 1280.185 -211.8) 
(list 1279.815 -211.8) 
(list 1279.8182 -213.4583) 
(list 1279.8213 -215.1167) 
(list 1279.8243 -216.775) 
(list 1279.8273 -218.4333) 
(list 1279.8303 -220.0917) 
(list 1279.8332 -221.75) 
(list 1279.836 -223.4083) 
(list 1279.8388 -225.0667) 
(list 1279.8416 -226.725) 
(list 1279.8443 -228.3833) 
(list 1279.8469 -230.0417) 
(list 1279.8496 -231.7) 
(list 1279.8521 -233.3583) 
(list 1279.8546 -235.0167) 
(list 1279.8571 -236.675) 
(list 1279.8595 -238.3333) 
(list 1279.8619 -239.9917) 
(list 1279.8642 -241.65) 
(list 1279.8665 -243.3083) 
(list 1279.8687 -244.9667) 
(list 1279.8709 -246.625) 
(list 1279.8731 -248.2833) 
(list 1279.8752 -249.9417) 
(list 1279.8772 -251.6) 
(list 1279.8792 -253.2583) 
(list 1279.8812 -254.9167) 
(list 1279.8832 -256.575) 
(list 1279.885 -258.2333) 
(list 1279.8869 -259.8917) 
(list 1279.8887 -261.55) 
(list 1279.8905 -263.2083) 
(list 1279.8922 -264.8667) 
(list 1279.8939 -266.525) 
(list 1279.8956 -268.1833) 
(list 1279.8972 -269.8417) 
(list 1279.8988 -271.5) 
(list 1279.9003 -273.1583) 
(list 1279.9018 -274.8167) 
(list 1279.9033 -276.475) 
(list 1279.9047 -278.1333) 
(list 1279.9061 -279.7917) 
(list 1279.9075 -281.45) 
(list 1279.9088 -283.1083) 
(list 1279.9101 -284.7667) 
(list 1279.9114 -286.425) 
(list 1279.9126 -288.0833) 
(list 1279.9138 -289.7417) 
(list 1279.915 -291.4) 
(list 1279.9161 -293.0583) 
(list 1279.9172 -294.7167) 
(list 1279.9183 -296.375) 
(list 1279.9193 -298.0333) 
(list 1279.9203 -299.6917) 
(list 1279.9213 -301.35) 
(list 1279.9222 -303.0083) 
(list 1279.9232 -304.6667) 
(list 1279.9241 -306.325) 
(list 1279.9249 -307.9833) 
(list 1279.9258 -309.6417) 
(list 1279.9266 -311.3) 
(list 1279.9273 -312.9583) 
(list 1279.9281 -314.6167) 
(list 1279.9288 -316.275) 
(list 1279.9295 -317.9333) 
(list 1279.9302 -319.5917) 
(list 1279.9309 -321.25) 
(list 1279.9315 -322.9083) 
(list 1279.9321 -324.5667) 
(list 1279.9327 -326.225) 
(list 1279.9333 -327.8833) 
(list 1279.9338 -329.5417) 
(list 1279.9343 -331.2) 
(list 1279.9348 -332.8583) 
(list 1279.9353 -334.5167) 
(list 1279.9358 -336.175) 
(list 1279.9362 -337.8333) 
(list 1279.9366 -339.4917) 
(list 1279.937 -341.15) 
(list 1279.9374 -342.8083) 
(list 1279.9378 -344.4667) 
(list 1279.9381 -346.125) 
(list 1279.9385 -347.7833) 
(list 1279.9388 -349.4417) 
(list 1279.9391 -351.1) 
(list 1279.9393 -352.7583) 
(list 1279.9396 -354.4167) 
(list 1279.9398 -356.075) 
(list 1279.9401 -357.7333) 
(list 1279.9403 -359.3917) 
(list 1279.9405 -361.05) 
(list 1279.9407 -362.7083) 
(list 1279.9409 -364.3667) 
(list 1279.941 -366.025) 
(list 1279.9412 -367.6833) 
(list 1279.9413 -369.3417) 
(list 1279.9415 -371) 
(list 1279.9416 -372.6583) 
(list 1279.9417 -374.3167) 
(list 1279.9418 -375.975) 
(list 1279.9419 -377.6333) 
(list 1279.942 -379.2917) 
(list 1279.9421 -380.95) 
(list 1279.9421 -382.6083) 
(list 1279.9422 -384.2667) 
(list 1279.9423 -385.925) 
(list 1279.9423 -387.5833) 
(list 1279.9423 -389.2417) 
(list 1279.9424 -390.9) 
(list 1279.9424 -392.5583) 
(list 1279.9424 -394.2167) 
(list 1279.9424 -395.875) 
(list 1279.9425 -397.5333) 
(list 1279.9425 -399.1917) 
(list 1279.9425 -400.85) 
(list 1279.9425 -402.5083) 
(list 1279.9425 -404.1667) 
(list 1279.9425 -405.825) 
(list 1279.9425 -407.4833) 
(list 1279.9425 -409.1417) 
(list 1279.9425 -410.8)))
(apply 'command (append '("pline") coords '("c")))
(setq currobj (ssadd (entlast) currobj))
(command "_layer" "set" "prebias" "")
(command "_rectangle" "1279.815,-410.8" "1280.185,-211.8")
(setq currobj (ssadd (entlast) currobj))
(command "_layer" "set" "nitride" "")
(setq singlenanobeam4 currobj)
(setq currobj nil)
(setq currobj (ssadd))
; DRAWING NODE ARRAY
(setq coords (list 
(list 1280.185 -211.8) 
(list 1280.5625 -201.8) 
(list 1280.5625 -201.8) 
(list 1280.5625 -200.8) 
(list 1354.585 -212.6864) 
(list 1354.585 -207.7434) 
(list 1280.5625 -197.357) 
(list 1280.5625 -196.357) 
(list 1280.5625 -196.357) 
(list 1280.2625 -186.357) 
(list 1279.7375 -186.357) 
(list 1279.4375 -196.357) 
(list 1279.4375 -196.357) 
(list 1279.4375 -197.357) 
(list 1205.415 -207.7434) 
(list 1205.415 -212.6864) 
(list 1279.4375 -200.8) 
(list 1279.4375 -201.8) 
(list 1279.4375 -201.8) 
(list 1279.815 -211.8)))
(apply 'command (append '("pline") coords '("c")))
(setq currobj (ssadd (entlast) currobj))
(command "_layer" "set" "prebias" "")
(setq coords (list 
(list 1279.4375 -212.6864) 
(list 1279.4375 -200.8) 
(list 1205.415 -212.6864) 
(list 1205.415 -207.7434) 
(list 1279.4375 -197.357) 
(list 1279.4375 -186.357) 
(list 1280.5625 -186.357) 
(list 1280.5625 -197.357) 
(list 1354.585 -207.7434) 
(list 1354.585 -212.6864) 
(list 1280.5625 -200.8) 
(list 1280.5625 -212.6864)))
(apply 'command (append '("pline") coords '("c")))
(setq currobj (ssadd (entlast) currobj))
(command "_layer" "set" "nitride" "")
(command "_layer" "set" "fda1" "")
(setq coords (list 
(list 1280.5625 -200.657) 
(list 1354.585 -212.5434) 
(list 1354.585 -212.3664) 
(list 1280.5625 -200.58)))
(apply 'command (append '("pline") coords '("c")))
(setq currobj (ssadd (entlast) currobj))
(setq coords (list 
(list 1280.5625 -200.437) 
(list 1354.585 -212.2234) 
(list 1354.585 -212.0464) 
(list 1280.5625 -200.36)))
(apply 'command (append '("pline") coords '("c")))
(setq currobj (ssadd (entlast) currobj))
(setq coords (list 
(list 1280.5625 -200.217) 
(list 1354.585 -211.9034) 
(list 1354.585 -211.7264) 
(list 1280.5625 -200.14)))
(apply 'command (append '("pline") coords '("c")))
(setq currobj (ssadd (entlast) currobj))
(setq coords (list 
(list 1280.5625 -199.997) 
(list 1354.585 -211.5834) 
(list 1354.585 -211.4064) 
(list 1280.5625 -199.92)))
(apply 'command (append '("pline") coords '("c")))
(setq currobj (ssadd (entlast) currobj))
(setq coords (list 
(list 1280.5625 -199.777) 
(list 1354.585 -211.2634) 
(list 1354.585 -211.0864) 
(list 1280.5625 -199.7)))
(apply 'command (append '("pline") coords '("c")))
(setq currobj (ssadd (entlast) currobj))
(setq coords (list 
(list 1280.5625 -199.557) 
(list 1354.585 -210.9434) 
(list 1354.585 -210.7664) 
(list 1280.5625 -199.48)))
(apply 'command (append '("pline") coords '("c")))
(setq currobj (ssadd (entlast) currobj))
(setq coords (list 
(list 1280.5625 -199.337) 
(list 1354.585 -210.6234) 
(list 1354.585 -210.4464) 
(list 1280.5625 -199.26)))
(apply 'command (append '("pline") coords '("c")))
(setq currobj (ssadd (entlast) currobj))
(setq coords (list 
(list 1280.5625 -199.117) 
(list 1354.585 -210.3034) 
(list 1354.585 -210.1264) 
(list 1280.5625 -199.04)))
(apply 'command (append '("pline") coords '("c")))
(setq currobj (ssadd (entlast) currobj))
(setq coords (list 
(list 1280.5625 -198.897) 
(list 1354.585 -209.9834) 
(list 1354.585 -209.8064) 
(list 1280.5625 -198.82)))
(apply 'command (append '("pline") coords '("c")))
(setq currobj (ssadd (entlast) currobj))
(setq coords (list 
(list 1280.5625 -198.677) 
(list 1354.585 -209.6634) 
(list 1354.585 -209.4864) 
(list 1280.5625 -198.6)))
(apply 'command (append '("pline") coords '("c")))
(setq currobj (ssadd (entlast) currobj))
(setq coords (list 
(list 1280.5625 -198.457) 
(list 1354.585 -209.3434) 
(list 1354.585 -209.1664) 
(list 1280.5625 -198.38)))
(apply 'command (append '("pline") coords '("c")))
(setq currobj (ssadd (entlast) currobj))
(setq coords (list 
(list 1280.5625 -198.237) 
(list 1354.585 -209.0234) 
(list 1354.585 -208.8464) 
(list 1280.5625 -198.16)))
(apply 'command (append '("pline") coords '("c")))
(setq currobj (ssadd (entlast) currobj))
(setq coords (list 
(list 1280.5625 -198.017) 
(list 1354.585 -208.7034) 
(list 1354.585 -208.5264) 
(list 1280.5625 -197.94)))
(apply 'command (append '("pline") coords '("c")))
(setq currobj (ssadd (entlast) currobj))
(setq coords (list 
(list 1280.5625 -197.797) 
(list 1354.585 -208.3834) 
(list 1354.585 -208.2064) 
(list 1280.5625 -197.72)))
(apply 'command (append '("pline") coords '("c")))
(setq currobj (ssadd (entlast) currobj))
(setq coords (list 
(list 1280.5625 -197.577) 
(list 1354.585 -208.0634) 
(list 1354.585 -207.8864) 
(list 1280.5625 -197.5)))
(apply 'command (append '("pline") coords '("c")))
(setq currobj (ssadd (entlast) currobj))
(setq coords (list 
(list 1279.4375 -197.5) 
(list 1205.415 -207.8864) 
(list 1205.415 -208.0634) 
(list 1279.4375 -197.577)))
(apply 'command (append '("pline") coords '("c")))
(setq currobj (ssadd (entlast) currobj))
(setq coords (list 
(list 1279.4375 -197.72) 
(list 1205.415 -208.2064) 
(list 1205.415 -208.3834) 
(list 1279.4375 -197.797)))
(apply 'command (append '("pline") coords '("c")))
(setq currobj (ssadd (entlast) currobj))
(setq coords (list 
(list 1279.4375 -197.94) 
(list 1205.415 -208.5264) 
(list 1205.415 -208.7034) 
(list 1279.4375 -198.017)))
(apply 'command (append '("pline") coords '("c")))
(setq currobj (ssadd (entlast) currobj))
(setq coords (list 
(list 1279.4375 -198.16) 
(list 1205.415 -208.8464) 
(list 1205.415 -209.0234) 
(list 1279.4375 -198.237)))
(apply 'command (append '("pline") coords '("c")))
(setq currobj (ssadd (entlast) currobj))
(setq coords (list 
(list 1279.4375 -198.38) 
(list 1205.415 -209.1664) 
(list 1205.415 -209.3434) 
(list 1279.4375 -198.457)))
(apply 'command (append '("pline") coords '("c")))
(setq currobj (ssadd (entlast) currobj))
(setq coords (list 
(list 1279.4375 -198.6) 
(list 1205.415 -209.4864) 
(list 1205.415 -209.6634) 
(list 1279.4375 -198.677)))
(apply 'command (append '("pline") coords '("c")))
(setq currobj (ssadd (entlast) currobj))
(setq coords (list 
(list 1279.4375 -198.82) 
(list 1205.415 -209.8064) 
(list 1205.415 -209.9834) 
(list 1279.4375 -198.897)))
(apply 'command (append '("pline") coords '("c")))
(setq currobj (ssadd (entlast) currobj))
(setq coords (list 
(list 1279.4375 -199.04) 
(list 1205.415 -210.1264) 
(list 1205.415 -210.3034) 
(list 1279.4375 -199.117)))
(apply 'command (append '("pline") coords '("c")))
(setq currobj (ssadd (entlast) currobj))
(setq coords (list 
(list 1279.4375 -199.26) 
(list 1205.415 -210.4464) 
(list 1205.415 -210.6234) 
(list 1279.4375 -199.337)))
(apply 'command (append '("pline") coords '("c")))
(setq currobj (ssadd (entlast) currobj))
(setq coords (list 
(list 1279.4375 -199.48) 
(list 1205.415 -210.7664) 
(list 1205.415 -210.9434) 
(list 1279.4375 -199.557)))
(apply 'command (append '("pline") coords '("c")))
(setq currobj (ssadd (entlast) currobj))
(setq coords (list 
(list 1279.4375 -199.7) 
(list 1205.415 -211.0864) 
(list 1205.415 -211.2634) 
(list 1279.4375 -199.777)))
(apply 'command (append '("pline") coords '("c")))
(setq currobj (ssadd (entlast) currobj))
(setq coords (list 
(list 1279.4375 -199.92) 
(list 1205.415 -211.4064) 
(list 1205.415 -211.5834) 
(list 1279.4375 -199.997)))
(apply 'command (append '("pline") coords '("c")))
(setq currobj (ssadd (entlast) currobj))
(setq coords (list 
(list 1279.4375 -200.14) 
(list 1205.415 -211.7264) 
(list 1205.415 -211.9034) 
(list 1279.4375 -200.217)))
(apply 'command (append '("pline") coords '("c")))
(setq currobj (ssadd (entlast) currobj))
(setq coords (list 
(list 1279.4375 -200.36) 
(list 1205.415 -212.0464) 
(list 1205.415 -212.2234) 
(list 1279.4375 -200.437)))
(apply 'command (append '("pline") coords '("c")))
(setq currobj (ssadd (entlast) currobj))
(setq coords (list 
(list 1279.4375 -200.58) 
(list 1205.415 -212.3664) 
(list 1205.415 -212.5434) 
(list 1279.4375 -200.657)))
(apply 'command (append '("pline") coords '("c")))
(setq currobj (ssadd (entlast) currobj))
(command "_layer" "set" "nitride" "")
(command "_layer" "set" "text" "")
(command "_circle" "1278.985,-211.8" "0.075")
(command "_circle" "1278.985,-211.5" "0.075")
(command "_circle" "1278.985,-211.2" "0.075")
(command "_circle" "1278.985,-210.9" "0.075")
(command "_circle" "1278.985,-210.6" "0.075")
(command "_circle" "1278.685,-211.8" "0.075")
(command "_circle" "1278.685,-211.5" "0.075")
(command "_circle" "1278.685,-211.2" "0.075")
(command "_circle" "1278.685,-210.9" "0.075")
(command "_circle" "1278.685,-210.6" "0.075")
(command "_circle" "1278.385,-211.8" "0.075")
(command "_circle" "1278.385,-211.5" "0.075")
(command "_circle" "1278.385,-211.2" "0.075")
(command "_circle" "1278.385,-210.9" "0.075")
(command "_circle" "1278.385,-210.6" "0.075")
(command "_circle" "1278.085,-211.8" "0.075")
(command "_circle" "1278.085,-211.5" "0.075")
(command "_circle" "1278.085,-211.2" "0.075")
(command "_circle" "1278.085,-210.9" "0.075")
(command "_circle" "1278.085,-210.6" "0.075")
(command "_circle" "1277.785,-211.8" "0.075")
(command "_circle" "1277.785,-211.5" "0.075")
(command "_circle" "1277.785,-211.2" "0.075")
(command "_circle" "1277.785,-210.9" "0.075")
(command "_circle" "1277.785,-210.6" "0.075")
(command "_layer" "set" "nitride" "")
(setq anglednodearray4 currobj)
(setq currobj nil)
(setq currobj (ssadd))
; DRAWING COOLED SINGLE NANOBEAM
(setq coords (list 
(list 1280.2625 -186.357) 
(list 1280.2625 -181.357) 
(list 1279.7375 -181.357) 
(list 1279.7375 -186.357)))
(apply 'command (append '("pline") coords '("c")))
(setq currobj (ssadd (entlast) currobj))
(command "_layer" "set" "prebias" "")
(command "_rectangle" "1279.7375,-186.357" "1280.2625,-181.357")
(setq currobj (ssadd (entlast) currobj))
(command "_layer" "set" "nitride" "")
(setq coords (list 
(list 1280.2625 -181.357) 
(list 1280.5625 -171.357) 
(list 1280.5625 -171.357) 
(list 1280.5625 -170.357) 
(list 1354.585 -171.107) 
(list 1354.585 -166.164) 
(list 1280.5625 -166.914) 
(list 1280.5625 -165.914) 
(list 1280.5625 -165.914) 
(list 1280.2625 -155.914) 
(list 1279.7375 -155.914) 
(list 1279.4375 -165.914) 
(list 1279.4375 -165.914) 
(list 1279.4375 -166.914) 
(list 1205.415 -166.164) 
(list 1205.415 -171.107) 
(list 1279.4375 -170.357) 
(list 1279.4375 -171.357) 
(list 1279.4375 -171.357) 
(list 1279.7375 -181.357)))
(apply 'command (append '("pline") coords '("c")))
(setq currobj (ssadd (entlast) currobj))
(command "_layer" "set" "prebias" "")
(setq coords (list 
(list 1279.4375 -181.357) 
(list 1279.4375 -170.357) 
(list 1205.415 -171.107) 
(list 1205.415 -166.164) 
(list 1279.4375 -166.914) 
(list 1279.4375 -155.914) 
(list 1280.5625 -155.914) 
(list 1280.5625 -166.914) 
(list 1354.585 -166.164) 
(list 1354.585 -171.107) 
(list 1280.5625 -170.357) 
(list 1280.5625 -181.357)))
(apply 'command (append '("pline") coords '("c")))
(setq currobj (ssadd (entlast) currobj))
(command "_layer" "set" "nitride" "")
(command "_layer" "set" "fda1" "")
(setq coords (list 
(list 1280.5625 -170.214) 
(list 1354.585 -170.964) 
(list 1354.585 -170.787) 
(list 1280.5625 -170.137)))
(apply 'command (append '("pline") coords '("c")))
(setq currobj (ssadd (entlast) currobj))
(setq coords (list 
(list 1280.5625 -169.994) 
(list 1354.585 -170.644) 
(list 1354.585 -170.467) 
(list 1280.5625 -169.917)))
(apply 'command (append '("pline") coords '("c")))
(setq currobj (ssadd (entlast) currobj))
(setq coords (list 
(list 1280.5625 -169.774) 
(list 1354.585 -170.324) 
(list 1354.585 -170.147) 
(list 1280.5625 -169.697)))
(apply 'command (append '("pline") coords '("c")))
(setq currobj (ssadd (entlast) currobj))
(setq coords (list 
(list 1280.5625 -169.554) 
(list 1354.585 -170.004) 
(list 1354.585 -169.827) 
(list 1280.5625 -169.477)))
(apply 'command (append '("pline") coords '("c")))
(setq currobj (ssadd (entlast) currobj))
(setq coords (list 
(list 1280.5625 -169.334) 
(list 1354.585 -169.684) 
(list 1354.585 -169.507) 
(list 1280.5625 -169.257)))
(apply 'command (append '("pline") coords '("c")))
(setq currobj (ssadd (entlast) currobj))
(setq coords (list 
(list 1280.5625 -169.114) 
(list 1354.585 -169.364) 
(list 1354.585 -169.187) 
(list 1280.5625 -169.037)))
(apply 'command (append '("pline") coords '("c")))
(setq currobj (ssadd (entlast) currobj))
(setq coords (list 
(list 1280.5625 -168.894) 
(list 1354.585 -169.044) 
(list 1354.585 -168.867) 
(list 1280.5625 -168.817)))
(apply 'command (append '("pline") coords '("c")))
(setq currobj (ssadd (entlast) currobj))
(setq coords (list 
(list 1280.5625 -168.674) 
(list 1354.585 -168.724) 
(list 1354.585 -168.547) 
(list 1280.5625 -168.597)))
(apply 'command (append '("pline") coords '("c")))
(setq currobj (ssadd (entlast) currobj))
(setq coords (list 
(list 1280.5625 -168.454) 
(list 1354.585 -168.404) 
(list 1354.585 -168.227) 
(list 1280.5625 -168.377)))
(apply 'command (append '("pline") coords '("c")))
(setq currobj (ssadd (entlast) currobj))
(setq coords (list 
(list 1280.5625 -168.234) 
(list 1354.585 -168.084) 
(list 1354.585 -167.907) 
(list 1280.5625 -168.157)))
(apply 'command (append '("pline") coords '("c")))
(setq currobj (ssadd (entlast) currobj))
(setq coords (list 
(list 1280.5625 -168.014) 
(list 1354.585 -167.764) 
(list 1354.585 -167.587) 
(list 1280.5625 -167.937)))
(apply 'command (append '("pline") coords '("c")))
(setq currobj (ssadd (entlast) currobj))
(setq coords (list 
(list 1280.5625 -167.794) 
(list 1354.585 -167.444) 
(list 1354.585 -167.267) 
(list 1280.5625 -167.717)))
(apply 'command (append '("pline") coords '("c")))
(setq currobj (ssadd (entlast) currobj))
(setq coords (list 
(list 1280.5625 -167.574) 
(list 1354.585 -167.124) 
(list 1354.585 -166.947) 
(list 1280.5625 -167.497)))
(apply 'command (append '("pline") coords '("c")))
(setq currobj (ssadd (entlast) currobj))
(setq coords (list 
(list 1280.5625 -167.354) 
(list 1354.585 -166.804) 
(list 1354.585 -166.627) 
(list 1280.5625 -167.277)))
(apply 'command (append '("pline") coords '("c")))
(setq currobj (ssadd (entlast) currobj))
(setq coords (list 
(list 1280.5625 -167.134) 
(list 1354.585 -166.484) 
(list 1354.585 -166.307) 
(list 1280.5625 -167.057)))
(apply 'command (append '("pline") coords '("c")))
(setq currobj (ssadd (entlast) currobj))
(setq coords (list 
(list 1279.4375 -167.057) 
(list 1205.415 -166.307) 
(list 1205.415 -166.484) 
(list 1279.4375 -167.134)))
(apply 'command (append '("pline") coords '("c")))
(setq currobj (ssadd (entlast) currobj))
(setq coords (list 
(list 1279.4375 -167.277) 
(list 1205.415 -166.627) 
(list 1205.415 -166.804) 
(list 1279.4375 -167.354)))
(apply 'command (append '("pline") coords '("c")))
(setq currobj (ssadd (entlast) currobj))
(setq coords (list 
(list 1279.4375 -167.497) 
(list 1205.415 -166.947) 
(list 1205.415 -167.124) 
(list 1279.4375 -167.574)))
(apply 'command (append '("pline") coords '("c")))
(setq currobj (ssadd (entlast) currobj))
(setq coords (list 
(list 1279.4375 -167.717) 
(list 1205.415 -167.267) 
(list 1205.415 -167.444) 
(list 1279.4375 -167.794)))
(apply 'command (append '("pline") coords '("c")))
(setq currobj (ssadd (entlast) currobj))
(setq coords (list 
(list 1279.4375 -167.937) 
(list 1205.415 -167.587) 
(list 1205.415 -167.764) 
(list 1279.4375 -168.014)))
(apply 'command (append '("pline") coords '("c")))
(setq currobj (ssadd (entlast) currobj))
(setq coords (list 
(list 1279.4375 -168.157) 
(list 1205.415 -167.907) 
(list 1205.415 -168.084) 
(list 1279.4375 -168.234)))
(apply 'command (append '("pline") coords '("c")))
(setq currobj (ssadd (entlast) currobj))
(setq coords (list 
(list 1279.4375 -168.377) 
(list 1205.415 -168.227) 
(list 1205.415 -168.404) 
(list 1279.4375 -168.454)))
(apply 'command (append '("pline") coords '("c")))
(setq currobj (ssadd (entlast) currobj))
(setq coords (list 
(list 1279.4375 -168.597) 
(list 1205.415 -168.547) 
(list 1205.415 -168.724) 
(list 1279.4375 -168.674)))
(apply 'command (append '("pline") coords '("c")))
(setq currobj (ssadd (entlast) currobj))
(setq coords (list 
(list 1279.4375 -168.817) 
(list 1205.415 -168.867) 
(list 1205.415 -169.044) 
(list 1279.4375 -168.894)))
(apply 'command (append '("pline") coords '("c")))
(setq currobj (ssadd (entlast) currobj))
(setq coords (list 
(list 1279.4375 -169.037) 
(list 1205.415 -169.187) 
(list 1205.415 -169.364) 
(list 1279.4375 -169.114)))
(apply 'command (append '("pline") coords '("c")))
(setq currobj (ssadd (entlast) currobj))
(setq coords (list 
(list 1279.4375 -169.257) 
(list 1205.415 -169.507) 
(list 1205.415 -169.684) 
(list 1279.4375 -169.334)))
(apply 'command (append '("pline") coords '("c")))
(setq currobj (ssadd (entlast) currobj))
(setq coords (list 
(list 1279.4375 -169.477) 
(list 1205.415 -169.827) 
(list 1205.415 -170.004) 
(list 1279.4375 -169.554)))
(apply 'command (append '("pline") coords '("c")))
(setq currobj (ssadd (entlast) currobj))
(setq coords (list 
(list 1279.4375 -169.697) 
(list 1205.415 -170.147) 
(list 1205.415 -170.324) 
(list 1279.4375 -169.774)))
(apply 'command (append '("pline") coords '("c")))
(setq currobj (ssadd (entlast) currobj))
(setq coords (list 
(list 1279.4375 -169.917) 
(list 1205.415 -170.467) 
(list 1205.415 -170.644) 
(list 1279.4375 -169.994)))
(apply 'command (append '("pline") coords '("c")))
(setq currobj (ssadd (entlast) currobj))
(setq coords (list 
(list 1279.4375 -170.137) 
(list 1205.415 -170.787) 
(list 1205.415 -170.964) 
(list 1279.4375 -170.214)))
(apply 'command (append '("pline") coords '("c")))
(setq currobj (ssadd (entlast) currobj))
(command "_layer" "set" "nitride" "")
(command "_layer" "set" "text" "")
(command "_circle" "1279.0625,-181.357" "0.075")
(command "_circle" "1279.0625,-181.057" "0.075")
(command "_circle" "1279.0625,-180.757" "0.075")
(command "_circle" "1279.0625,-180.457" "0.075")
(command "_circle" "1279.0625,-180.157" "0.075")
(command "_circle" "1278.7625,-181.357" "0.075")
(command "_circle" "1278.7625,-181.057" "0.075")
(command "_circle" "1278.7625,-180.757" "0.075")
(command "_circle" "1278.7625,-180.457" "0.075")
(command "_circle" "1278.7625,-180.157" "0.075")
(command "_circle" "1278.4625,-181.357" "0.075")
(command "_circle" "1278.4625,-181.057" "0.075")
(command "_circle" "1278.4625,-180.757" "0.075")
(command "_circle" "1278.4625,-180.457" "0.075")
(command "_circle" "1278.4625,-180.157" "0.075")
(command "_circle" "1278.1625,-181.357" "0.075")
(command "_circle" "1278.1625,-181.057" "0.075")
(command "_circle" "1278.1625,-180.757" "0.075")
(command "_circle" "1278.1625,-180.457" "0.075")
(command "_circle" "1278.1625,-180.157" "0.075")
(command "_circle" "1277.8625,-181.357" "0.075")
(command "_circle" "1277.8625,-181.057" "0.075")
(command "_circle" "1277.8625,-180.757" "0.075")
(command "_circle" "1277.8625,-180.457" "0.075")
(command "_circle" "1277.8625,-180.157" "0.075")
(command "_layer" "set" "nitride" "")
(setq coords (list 
(list 1280.2625 -155.914) 
(list 1280.2625 -40.2693) 
(list 1279.7375 -40.2693) 
(list 1279.7375 -155.914)))
(apply 'command (append '("pline") coords '("c")))
(setq currobj (ssadd (entlast) currobj))
(command "_layer" "set" "prebias" "")
(command "_rectangle" "1279.7375,-155.914" "1280.2625,-40.2693")
(setq currobj (ssadd (entlast) currobj))
(command "_layer" "set" "nitride" "")
(setq coords (list 
(list 1280.2625 -40.2693) 
(list 1280.5625 -30.2693) 
(list 1280.5625 -30.2693) 
(list 1280.5625 -29.2693) 
(list 1354.585 -30.0193) 
(list 1354.585 -25.0763) 
(list 1280.5625 -25.8263) 
(list 1280.5625 -24.8263) 
(list 1280.5625 -24.8263) 
(list 1280.2625 -14.8263) 
(list 1279.7375 -14.8263) 
(list 1279.4375 -24.8263) 
(list 1279.4375 -24.8263) 
(list 1279.4375 -25.8263) 
(list 1205.415 -25.0763) 
(list 1205.415 -30.0193) 
(list 1279.4375 -29.2693) 
(list 1279.4375 -30.2693) 
(list 1279.4375 -30.2693) 
(list 1279.7375 -40.2693)))
(apply 'command (append '("pline") coords '("c")))
(setq currobj (ssadd (entlast) currobj))
(command "_layer" "set" "prebias" "")
(setq coords (list 
(list 1279.4375 -40.2693) 
(list 1279.4375 -29.2693) 
(list 1205.415 -30.0193) 
(list 1205.415 -25.0763) 
(list 1279.4375 -25.8263) 
(list 1279.4375 -14.8263) 
(list 1280.5625 -14.8263) 
(list 1280.5625 -25.8263) 
(list 1354.585 -25.0763) 
(list 1354.585 -30.0193) 
(list 1280.5625 -29.2693) 
(list 1280.5625 -40.2693)))
(apply 'command (append '("pline") coords '("c")))
(setq currobj (ssadd (entlast) currobj))
(command "_layer" "set" "nitride" "")
(command "_layer" "set" "fda1" "")
(setq coords (list 
(list 1280.5625 -29.1263) 
(list 1354.585 -29.8763) 
(list 1354.585 -29.6993) 
(list 1280.5625 -29.0493)))
(apply 'command (append '("pline") coords '("c")))
(setq currobj (ssadd (entlast) currobj))
(setq coords (list 
(list 1280.5625 -28.9063) 
(list 1354.585 -29.5563) 
(list 1354.585 -29.3793) 
(list 1280.5625 -28.8293)))
(apply 'command (append '("pline") coords '("c")))
(setq currobj (ssadd (entlast) currobj))
(setq coords (list 
(list 1280.5625 -28.6863) 
(list 1354.585 -29.2363) 
(list 1354.585 -29.0593) 
(list 1280.5625 -28.6093)))
(apply 'command (append '("pline") coords '("c")))
(setq currobj (ssadd (entlast) currobj))
(setq coords (list 
(list 1280.5625 -28.4663) 
(list 1354.585 -28.9163) 
(list 1354.585 -28.7393) 
(list 1280.5625 -28.3893)))
(apply 'command (append '("pline") coords '("c")))
(setq currobj (ssadd (entlast) currobj))
(setq coords (list 
(list 1280.5625 -28.2463) 
(list 1354.585 -28.5963) 
(list 1354.585 -28.4193) 
(list 1280.5625 -28.1693)))
(apply 'command (append '("pline") coords '("c")))
(setq currobj (ssadd (entlast) currobj))
(setq coords (list 
(list 1280.5625 -28.0263) 
(list 1354.585 -28.2763) 
(list 1354.585 -28.0993) 
(list 1280.5625 -27.9493)))
(apply 'command (append '("pline") coords '("c")))
(setq currobj (ssadd (entlast) currobj))
(setq coords (list 
(list 1280.5625 -27.8063) 
(list 1354.585 -27.9563) 
(list 1354.585 -27.7793) 
(list 1280.5625 -27.7293)))
(apply 'command (append '("pline") coords '("c")))
(setq currobj (ssadd (entlast) currobj))
(setq coords (list 
(list 1280.5625 -27.5863) 
(list 1354.585 -27.6363) 
(list 1354.585 -27.4593) 
(list 1280.5625 -27.5093)))
(apply 'command (append '("pline") coords '("c")))
(setq currobj (ssadd (entlast) currobj))
(setq coords (list 
(list 1280.5625 -27.3663) 
(list 1354.585 -27.3163) 
(list 1354.585 -27.1393) 
(list 1280.5625 -27.2893)))
(apply 'command (append '("pline") coords '("c")))
(setq currobj (ssadd (entlast) currobj))
(setq coords (list 
(list 1280.5625 -27.1463) 
(list 1354.585 -26.9963) 
(list 1354.585 -26.8193) 
(list 1280.5625 -27.0693)))
(apply 'command (append '("pline") coords '("c")))
(setq currobj (ssadd (entlast) currobj))
(setq coords (list 
(list 1280.5625 -26.9263) 
(list 1354.585 -26.6763) 
(list 1354.585 -26.4993) 
(list 1280.5625 -26.8493)))
(apply 'command (append '("pline") coords '("c")))
(setq currobj (ssadd (entlast) currobj))
(setq coords (list 
(list 1280.5625 -26.7063) 
(list 1354.585 -26.3563) 
(list 1354.585 -26.1793) 
(list 1280.5625 -26.6293)))
(apply 'command (append '("pline") coords '("c")))
(setq currobj (ssadd (entlast) currobj))
(setq coords (list 
(list 1280.5625 -26.4863) 
(list 1354.585 -26.0363) 
(list 1354.585 -25.8593) 
(list 1280.5625 -26.4093)))
(apply 'command (append '("pline") coords '("c")))
(setq currobj (ssadd (entlast) currobj))
(setq coords (list 
(list 1280.5625 -26.2663) 
(list 1354.585 -25.7163) 
(list 1354.585 -25.5393) 
(list 1280.5625 -26.1893)))
(apply 'command (append '("pline") coords '("c")))
(setq currobj (ssadd (entlast) currobj))
(setq coords (list 
(list 1280.5625 -26.0463) 
(list 1354.585 -25.3963) 
(list 1354.585 -25.2193) 
(list 1280.5625 -25.9693)))
(apply 'command (append '("pline") coords '("c")))
(setq currobj (ssadd (entlast) currobj))
(setq coords (list 
(list 1279.4375 -25.9693) 
(list 1205.415 -25.2193) 
(list 1205.415 -25.3963) 
(list 1279.4375 -26.0463)))
(apply 'command (append '("pline") coords '("c")))
(setq currobj (ssadd (entlast) currobj))
(setq coords (list 
(list 1279.4375 -26.1893) 
(list 1205.415 -25.5393) 
(list 1205.415 -25.7163) 
(list 1279.4375 -26.2663)))
(apply 'command (append '("pline") coords '("c")))
(setq currobj (ssadd (entlast) currobj))
(setq coords (list 
(list 1279.4375 -26.4093) 
(list 1205.415 -25.8593) 
(list 1205.415 -26.0363) 
(list 1279.4375 -26.4863)))
(apply 'command (append '("pline") coords '("c")))
(setq currobj (ssadd (entlast) currobj))
(setq coords (list 
(list 1279.4375 -26.6293) 
(list 1205.415 -26.1793) 
(list 1205.415 -26.3563) 
(list 1279.4375 -26.7063)))
(apply 'command (append '("pline") coords '("c")))
(setq currobj (ssadd (entlast) currobj))
(setq coords (list 
(list 1279.4375 -26.8493) 
(list 1205.415 -26.4993) 
(list 1205.415 -26.6763) 
(list 1279.4375 -26.9263)))
(apply 'command (append '("pline") coords '("c")))
(setq currobj (ssadd (entlast) currobj))
(setq coords (list 
(list 1279.4375 -27.0693) 
(list 1205.415 -26.8193) 
(list 1205.415 -26.9963) 
(list 1279.4375 -27.1463)))
(apply 'command (append '("pline") coords '("c")))
(setq currobj (ssadd (entlast) currobj))
(setq coords (list 
(list 1279.4375 -27.2893) 
(list 1205.415 -27.1393) 
(list 1205.415 -27.3163) 
(list 1279.4375 -27.3663)))
(apply 'command (append '("pline") coords '("c")))
(setq currobj (ssadd (entlast) currobj))
(setq coords (list 
(list 1279.4375 -27.5093) 
(list 1205.415 -27.4593) 
(list 1205.415 -27.6363) 
(list 1279.4375 -27.5863)))
(apply 'command (append '("pline") coords '("c")))
(setq currobj (ssadd (entlast) currobj))
(setq coords (list 
(list 1279.4375 -27.7293) 
(list 1205.415 -27.7793) 
(list 1205.415 -27.9563) 
(list 1279.4375 -27.8063)))
(apply 'command (append '("pline") coords '("c")))
(setq currobj (ssadd (entlast) currobj))
(setq coords (list 
(list 1279.4375 -27.9493) 
(list 1205.415 -28.0993) 
(list 1205.415 -28.2763) 
(list 1279.4375 -28.0263)))
(apply 'command (append '("pline") coords '("c")))
(setq currobj (ssadd (entlast) currobj))
(setq coords (list 
(list 1279.4375 -28.1693) 
(list 1205.415 -28.4193) 
(list 1205.415 -28.5963) 
(list 1279.4375 -28.2463)))
(apply 'command (append '("pline") coords '("c")))
(setq currobj (ssadd (entlast) currobj))
(setq coords (list 
(list 1279.4375 -28.3893) 
(list 1205.415 -28.7393) 
(list 1205.415 -28.9163) 
(list 1279.4375 -28.4663)))
(apply 'command (append '("pline") coords '("c")))
(setq currobj (ssadd (entlast) currobj))
(setq coords (list 
(list 1279.4375 -28.6093) 
(list 1205.415 -29.0593) 
(list 1205.415 -29.2363) 
(list 1279.4375 -28.6863)))
(apply 'command (append '("pline") coords '("c")))
(setq currobj (ssadd (entlast) currobj))
(setq coords (list 
(list 1279.4375 -28.8293) 
(list 1205.415 -29.3793) 
(list 1205.415 -29.5563) 
(list 1279.4375 -28.9063)))
(apply 'command (append '("pline") coords '("c")))
(setq currobj (ssadd (entlast) currobj))
(setq coords (list 
(list 1279.4375 -29.0493) 
(list 1205.415 -29.6993) 
(list 1205.415 -29.8763) 
(list 1279.4375 -29.1263)))
(apply 'command (append '("pline") coords '("c")))
(setq currobj (ssadd (entlast) currobj))
(command "_layer" "set" "nitride" "")
(command "_layer" "set" "text" "")
(command "_circle" "1279.0625,-40.2693" "0.075")
(command "_circle" "1279.0625,-39.9693" "0.075")
(command "_circle" "1279.0625,-39.6693" "0.075")
(command "_circle" "1279.0625,-39.3693" "0.075")
(command "_circle" "1279.0625,-39.0693" "0.075")
(command "_circle" "1278.7625,-40.2693" "0.075")
(command "_circle" "1278.7625,-39.9693" "0.075")
(command "_circle" "1278.7625,-39.6693" "0.075")
(command "_circle" "1278.7625,-39.3693" "0.075")
(command "_circle" "1278.7625,-39.0693" "0.075")
(command "_circle" "1278.4625,-40.2693" "0.075")
(command "_circle" "1278.4625,-39.9693" "0.075")
(command "_circle" "1278.4625,-39.6693" "0.075")
(command "_circle" "1278.4625,-39.3693" "0.075")
(command "_circle" "1278.4625,-39.0693" "0.075")
(command "_circle" "1278.1625,-40.2693" "0.075")
(command "_circle" "1278.1625,-39.9693" "0.075")
(command "_circle" "1278.1625,-39.6693" "0.075")
(command "_circle" "1278.1625,-39.3693" "0.075")
(command "_circle" "1278.1625,-39.0693" "0.075")
(command "_circle" "1277.8625,-40.2693" "0.075")
(command "_circle" "1277.8625,-39.9693" "0.075")
(command "_circle" "1277.8625,-39.6693" "0.075")
(command "_circle" "1277.8625,-39.3693" "0.075")
(command "_circle" "1277.8625,-39.0693" "0.075")
(command "_layer" "set" "nitride" "")
(setq coords (list 
(list 1280.2625 -14.8263) 
(list 1280.2625 100.8184) 
(list 1279.7375 100.8184) 
(list 1279.7375 -14.8263)))
(apply 'command (append '("pline") coords '("c")))
(setq currobj (ssadd (entlast) currobj))
(command "_layer" "set" "prebias" "")
(command "_rectangle" "1279.7375,-14.8263" "1280.2625,100.8184")
(setq currobj (ssadd (entlast) currobj))
(command "_layer" "set" "nitride" "")
(setq coords (list 
(list 1280.2625 100.8184) 
(list 1280.5625 110.8184) 
(list 1280.5625 110.8184) 
(list 1280.5625 111.8184) 
(list 1354.585 111.0684) 
(list 1354.585 116.0114) 
(list 1280.5625 115.2614) 
(list 1280.5625 116.2614) 
(list 1280.5625 116.2614) 
(list 1280.2625 126.2614) 
(list 1279.7375 126.2614) 
(list 1279.4375 116.2614) 
(list 1279.4375 116.2614) 
(list 1279.4375 115.2614) 
(list 1205.415 116.0114) 
(list 1205.415 111.0684) 
(list 1279.4375 111.8184) 
(list 1279.4375 110.8184) 
(list 1279.4375 110.8184) 
(list 1279.7375 100.8184)))
(apply 'command (append '("pline") coords '("c")))
(setq currobj (ssadd (entlast) currobj))
(command "_layer" "set" "prebias" "")
(setq coords (list 
(list 1279.4375 100.8184) 
(list 1279.4375 111.8184) 
(list 1205.415 111.0684) 
(list 1205.415 116.0114) 
(list 1279.4375 115.2614) 
(list 1279.4375 126.2614) 
(list 1280.5625 126.2614) 
(list 1280.5625 115.2614) 
(list 1354.585 116.0114) 
(list 1354.585 111.0684) 
(list 1280.5625 111.8184) 
(list 1280.5625 100.8184)))
(apply 'command (append '("pline") coords '("c")))
(setq currobj (ssadd (entlast) currobj))
(command "_layer" "set" "nitride" "")
(command "_layer" "set" "fda1" "")
(setq coords (list 
(list 1280.5625 111.9614) 
(list 1354.585 111.2114) 
(list 1354.585 111.3884) 
(list 1280.5625 112.0384)))
(apply 'command (append '("pline") coords '("c")))
(setq currobj (ssadd (entlast) currobj))
(setq coords (list 
(list 1280.5625 112.1814) 
(list 1354.585 111.5314) 
(list 1354.585 111.7084) 
(list 1280.5625 112.2584)))
(apply 'command (append '("pline") coords '("c")))
(setq currobj (ssadd (entlast) currobj))
(setq coords (list 
(list 1280.5625 112.4014) 
(list 1354.585 111.8514) 
(list 1354.585 112.0284) 
(list 1280.5625 112.4784)))
(apply 'command (append '("pline") coords '("c")))
(setq currobj (ssadd (entlast) currobj))
(setq coords (list 
(list 1280.5625 112.6214) 
(list 1354.585 112.1714) 
(list 1354.585 112.3484) 
(list 1280.5625 112.6984)))
(apply 'command (append '("pline") coords '("c")))
(setq currobj (ssadd (entlast) currobj))
(setq coords (list 
(list 1280.5625 112.8414) 
(list 1354.585 112.4914) 
(list 1354.585 112.6684) 
(list 1280.5625 112.9184)))
(apply 'command (append '("pline") coords '("c")))
(setq currobj (ssadd (entlast) currobj))
(setq coords (list 
(list 1280.5625 113.0614) 
(list 1354.585 112.8114) 
(list 1354.585 112.9884) 
(list 1280.5625 113.1384)))
(apply 'command (append '("pline") coords '("c")))
(setq currobj (ssadd (entlast) currobj))
(setq coords (list 
(list 1280.5625 113.2814) 
(list 1354.585 113.1314) 
(list 1354.585 113.3084) 
(list 1280.5625 113.3584)))
(apply 'command (append '("pline") coords '("c")))
(setq currobj (ssadd (entlast) currobj))
(setq coords (list 
(list 1280.5625 113.5014) 
(list 1354.585 113.4514) 
(list 1354.585 113.6284) 
(list 1280.5625 113.5784)))
(apply 'command (append '("pline") coords '("c")))
(setq currobj (ssadd (entlast) currobj))
(setq coords (list 
(list 1280.5625 113.7214) 
(list 1354.585 113.7714) 
(list 1354.585 113.9484) 
(list 1280.5625 113.7984)))
(apply 'command (append '("pline") coords '("c")))
(setq currobj (ssadd (entlast) currobj))
(setq coords (list 
(list 1280.5625 113.9414) 
(list 1354.585 114.0914) 
(list 1354.585 114.2684) 
(list 1280.5625 114.0184)))
(apply 'command (append '("pline") coords '("c")))
(setq currobj (ssadd (entlast) currobj))
(setq coords (list 
(list 1280.5625 114.1614) 
(list 1354.585 114.4114) 
(list 1354.585 114.5884) 
(list 1280.5625 114.2384)))
(apply 'command (append '("pline") coords '("c")))
(setq currobj (ssadd (entlast) currobj))
(setq coords (list 
(list 1280.5625 114.3814) 
(list 1354.585 114.7314) 
(list 1354.585 114.9084) 
(list 1280.5625 114.4584)))
(apply 'command (append '("pline") coords '("c")))
(setq currobj (ssadd (entlast) currobj))
(setq coords (list 
(list 1280.5625 114.6014) 
(list 1354.585 115.0514) 
(list 1354.585 115.2284) 
(list 1280.5625 114.6784)))
(apply 'command (append '("pline") coords '("c")))
(setq currobj (ssadd (entlast) currobj))
(setq coords (list 
(list 1280.5625 114.8214) 
(list 1354.585 115.3714) 
(list 1354.585 115.5484) 
(list 1280.5625 114.8984)))
(apply 'command (append '("pline") coords '("c")))
(setq currobj (ssadd (entlast) currobj))
(setq coords (list 
(list 1280.5625 115.0414) 
(list 1354.585 115.6914) 
(list 1354.585 115.8684) 
(list 1280.5625 115.1184)))
(apply 'command (append '("pline") coords '("c")))
(setq currobj (ssadd (entlast) currobj))
(setq coords (list 
(list 1279.4375 115.1184) 
(list 1205.415 115.8684) 
(list 1205.415 115.6914) 
(list 1279.4375 115.0414)))
(apply 'command (append '("pline") coords '("c")))
(setq currobj (ssadd (entlast) currobj))
(setq coords (list 
(list 1279.4375 114.8984) 
(list 1205.415 115.5484) 
(list 1205.415 115.3714) 
(list 1279.4375 114.8214)))
(apply 'command (append '("pline") coords '("c")))
(setq currobj (ssadd (entlast) currobj))
(setq coords (list 
(list 1279.4375 114.6784) 
(list 1205.415 115.2284) 
(list 1205.415 115.0514) 
(list 1279.4375 114.6014)))
(apply 'command (append '("pline") coords '("c")))
(setq currobj (ssadd (entlast) currobj))
(setq coords (list 
(list 1279.4375 114.4584) 
(list 1205.415 114.9084) 
(list 1205.415 114.7314) 
(list 1279.4375 114.3814)))
(apply 'command (append '("pline") coords '("c")))
(setq currobj (ssadd (entlast) currobj))
(setq coords (list 
(list 1279.4375 114.2384) 
(list 1205.415 114.5884) 
(list 1205.415 114.4114) 
(list 1279.4375 114.1614)))
(apply 'command (append '("pline") coords '("c")))
(setq currobj (ssadd (entlast) currobj))
(setq coords (list 
(list 1279.4375 114.0184) 
(list 1205.415 114.2684) 
(list 1205.415 114.0914) 
(list 1279.4375 113.9414)))
(apply 'command (append '("pline") coords '("c")))
(setq currobj (ssadd (entlast) currobj))
(setq coords (list 
(list 1279.4375 113.7984) 
(list 1205.415 113.9484) 
(list 1205.415 113.7714) 
(list 1279.4375 113.7214)))
(apply 'command (append '("pline") coords '("c")))
(setq currobj (ssadd (entlast) currobj))
(setq coords (list 
(list 1279.4375 113.5784) 
(list 1205.415 113.6284) 
(list 1205.415 113.4514) 
(list 1279.4375 113.5014)))
(apply 'command (append '("pline") coords '("c")))
(setq currobj (ssadd (entlast) currobj))
(setq coords (list 
(list 1279.4375 113.3584) 
(list 1205.415 113.3084) 
(list 1205.415 113.1314) 
(list 1279.4375 113.2814)))
(apply 'command (append '("pline") coords '("c")))
(setq currobj (ssadd (entlast) currobj))
(setq coords (list 
(list 1279.4375 113.1384) 
(list 1205.415 112.9884) 
(list 1205.415 112.8114) 
(list 1279.4375 113.0614)))
(apply 'command (append '("pline") coords '("c")))
(setq currobj (ssadd (entlast) currobj))
(setq coords (list 
(list 1279.4375 112.9184) 
(list 1205.415 112.6684) 
(list 1205.415 112.4914) 
(list 1279.4375 112.8414)))
(apply 'command (append '("pline") coords '("c")))
(setq currobj (ssadd (entlast) currobj))
(setq coords (list 
(list 1279.4375 112.6984) 
(list 1205.415 112.3484) 
(list 1205.415 112.1714) 
(list 1279.4375 112.6214)))
(apply 'command (append '("pline") coords '("c")))
(setq currobj (ssadd (entlast) currobj))
(setq coords (list 
(list 1279.4375 112.4784) 
(list 1205.415 112.0284) 
(list 1205.415 111.8514) 
(list 1279.4375 112.4014)))
(apply 'command (append '("pline") coords '("c")))
(setq currobj (ssadd (entlast) currobj))
(setq coords (list 
(list 1279.4375 112.2584) 
(list 1205.415 111.7084) 
(list 1205.415 111.5314) 
(list 1279.4375 112.1814)))
(apply 'command (append '("pline") coords '("c")))
(setq currobj (ssadd (entlast) currobj))
(setq coords (list 
(list 1279.4375 112.0384) 
(list 1205.415 111.3884) 
(list 1205.415 111.2114) 
(list 1279.4375 111.9614)))
(apply 'command (append '("pline") coords '("c")))
(setq currobj (ssadd (entlast) currobj))
(command "_layer" "set" "nitride" "")
(command "_layer" "set" "text" "")
(command "_circle" "1279.0625,100.8184" "0.075")
(command "_circle" "1279.0625,101.1184" "0.075")
(command "_circle" "1279.0625,101.4184" "0.075")
(command "_circle" "1279.0625,101.7184" "0.075")
(command "_circle" "1279.0625,102.0184" "0.075")
(command "_circle" "1278.7625,100.8184" "0.075")
(command "_circle" "1278.7625,101.1184" "0.075")
(command "_circle" "1278.7625,101.4184" "0.075")
(command "_circle" "1278.7625,101.7184" "0.075")
(command "_circle" "1278.7625,102.0184" "0.075")
(command "_circle" "1278.4625,100.8184" "0.075")
(command "_circle" "1278.4625,101.1184" "0.075")
(command "_circle" "1278.4625,101.4184" "0.075")
(command "_circle" "1278.4625,101.7184" "0.075")
(command "_circle" "1278.4625,102.0184" "0.075")
(command "_circle" "1278.1625,100.8184" "0.075")
(command "_circle" "1278.1625,101.1184" "0.075")
(command "_circle" "1278.1625,101.4184" "0.075")
(command "_circle" "1278.1625,101.7184" "0.075")
(command "_circle" "1278.1625,102.0184" "0.075")
(command "_circle" "1277.8625,100.8184" "0.075")
(command "_circle" "1277.8625,101.1184" "0.075")
(command "_circle" "1277.8625,101.4184" "0.075")
(command "_circle" "1277.8625,101.7184" "0.075")
(command "_circle" "1277.8625,102.0184" "0.075")
(command "_layer" "set" "nitride" "")
(setq coords (list 
(list 1280.2625 126.2614) 
(list 1280.2625 241.9061) 
(list 1279.7375 241.9061) 
(list 1279.7375 126.2614)))
(apply 'command (append '("pline") coords '("c")))
(setq currobj (ssadd (entlast) currobj))
(command "_layer" "set" "prebias" "")
(command "_rectangle" "1279.7375,126.2614" "1280.2625,241.9061")
(setq currobj (ssadd (entlast) currobj))
(command "_layer" "set" "nitride" "")
(setq coords (list 
(list 1280.2625 241.9061) 
(list 1280.5625 251.9061) 
(list 1280.5625 251.9061) 
(list 1280.5625 252.9061) 
(list 1354.585 252.1561) 
(list 1354.585 257.0991) 
(list 1280.5625 256.3491) 
(list 1280.5625 257.3491) 
(list 1280.5625 257.3491) 
(list 1280.2625 267.3491) 
(list 1279.7375 267.3491) 
(list 1279.4375 257.3491) 
(list 1279.4375 257.3491) 
(list 1279.4375 256.3491) 
(list 1205.415 257.0991) 
(list 1205.415 252.1561) 
(list 1279.4375 252.9061) 
(list 1279.4375 251.9061) 
(list 1279.4375 251.9061) 
(list 1279.7375 241.9061)))
(apply 'command (append '("pline") coords '("c")))
(setq currobj (ssadd (entlast) currobj))
(command "_layer" "set" "prebias" "")
(setq coords (list 
(list 1279.4375 241.9061) 
(list 1279.4375 252.9061) 
(list 1205.415 252.1561) 
(list 1205.415 257.0991) 
(list 1279.4375 256.3491) 
(list 1279.4375 267.3491) 
(list 1280.5625 267.3491) 
(list 1280.5625 256.3491) 
(list 1354.585 257.0991) 
(list 1354.585 252.1561) 
(list 1280.5625 252.9061) 
(list 1280.5625 241.9061)))
(apply 'command (append '("pline") coords '("c")))
(setq currobj (ssadd (entlast) currobj))
(command "_layer" "set" "nitride" "")
(command "_layer" "set" "fda1" "")
(setq coords (list 
(list 1280.5625 253.0491) 
(list 1354.585 252.2991) 
(list 1354.585 252.4761) 
(list 1280.5625 253.1261)))
(apply 'command (append '("pline") coords '("c")))
(setq currobj (ssadd (entlast) currobj))
(setq coords (list 
(list 1280.5625 253.2691) 
(list 1354.585 252.6191) 
(list 1354.585 252.7961) 
(list 1280.5625 253.3461)))
(apply 'command (append '("pline") coords '("c")))
(setq currobj (ssadd (entlast) currobj))
(setq coords (list 
(list 1280.5625 253.4891) 
(list 1354.585 252.9391) 
(list 1354.585 253.1161) 
(list 1280.5625 253.5661)))
(apply 'command (append '("pline") coords '("c")))
(setq currobj (ssadd (entlast) currobj))
(setq coords (list 
(list 1280.5625 253.7091) 
(list 1354.585 253.2591) 
(list 1354.585 253.4361) 
(list 1280.5625 253.7861)))
(apply 'command (append '("pline") coords '("c")))
(setq currobj (ssadd (entlast) currobj))
(setq coords (list 
(list 1280.5625 253.9291) 
(list 1354.585 253.5791) 
(list 1354.585 253.7561) 
(list 1280.5625 254.0061)))
(apply 'command (append '("pline") coords '("c")))
(setq currobj (ssadd (entlast) currobj))
(setq coords (list 
(list 1280.5625 254.1491) 
(list 1354.585 253.8991) 
(list 1354.585 254.0761) 
(list 1280.5625 254.2261)))
(apply 'command (append '("pline") coords '("c")))
(setq currobj (ssadd (entlast) currobj))
(setq coords (list 
(list 1280.5625 254.3691) 
(list 1354.585 254.2191) 
(list 1354.585 254.3961) 
(list 1280.5625 254.4461)))
(apply 'command (append '("pline") coords '("c")))
(setq currobj (ssadd (entlast) currobj))
(setq coords (list 
(list 1280.5625 254.5891) 
(list 1354.585 254.5391) 
(list 1354.585 254.7161) 
(list 1280.5625 254.6661)))
(apply 'command (append '("pline") coords '("c")))
(setq currobj (ssadd (entlast) currobj))
(setq coords (list 
(list 1280.5625 254.8091) 
(list 1354.585 254.8591) 
(list 1354.585 255.0361) 
(list 1280.5625 254.8861)))
(apply 'command (append '("pline") coords '("c")))
(setq currobj (ssadd (entlast) currobj))
(setq coords (list 
(list 1280.5625 255.0291) 
(list 1354.585 255.1791) 
(list 1354.585 255.3561) 
(list 1280.5625 255.1061)))
(apply 'command (append '("pline") coords '("c")))
(setq currobj (ssadd (entlast) currobj))
(setq coords (list 
(list 1280.5625 255.2491) 
(list 1354.585 255.4991) 
(list 1354.585 255.6761) 
(list 1280.5625 255.3261)))
(apply 'command (append '("pline") coords '("c")))
(setq currobj (ssadd (entlast) currobj))
(setq coords (list 
(list 1280.5625 255.4691) 
(list 1354.585 255.8191) 
(list 1354.585 255.9961) 
(list 1280.5625 255.5461)))
(apply 'command (append '("pline") coords '("c")))
(setq currobj (ssadd (entlast) currobj))
(setq coords (list 
(list 1280.5625 255.6891) 
(list 1354.585 256.1391) 
(list 1354.585 256.3161) 
(list 1280.5625 255.7661)))
(apply 'command (append '("pline") coords '("c")))
(setq currobj (ssadd (entlast) currobj))
(setq coords (list 
(list 1280.5625 255.9091) 
(list 1354.585 256.4591) 
(list 1354.585 256.6361) 
(list 1280.5625 255.9861)))
(apply 'command (append '("pline") coords '("c")))
(setq currobj (ssadd (entlast) currobj))
(setq coords (list 
(list 1280.5625 256.1291) 
(list 1354.585 256.7791) 
(list 1354.585 256.9561) 
(list 1280.5625 256.2061)))
(apply 'command (append '("pline") coords '("c")))
(setq currobj (ssadd (entlast) currobj))
(setq coords (list 
(list 1279.4375 256.2061) 
(list 1205.415 256.9561) 
(list 1205.415 256.7791) 
(list 1279.4375 256.1291)))
(apply 'command (append '("pline") coords '("c")))
(setq currobj (ssadd (entlast) currobj))
(setq coords (list 
(list 1279.4375 255.9861) 
(list 1205.415 256.6361) 
(list 1205.415 256.4591) 
(list 1279.4375 255.9091)))
(apply 'command (append '("pline") coords '("c")))
(setq currobj (ssadd (entlast) currobj))
(setq coords (list 
(list 1279.4375 255.7661) 
(list 1205.415 256.3161) 
(list 1205.415 256.1391) 
(list 1279.4375 255.6891)))
(apply 'command (append '("pline") coords '("c")))
(setq currobj (ssadd (entlast) currobj))
(setq coords (list 
(list 1279.4375 255.5461) 
(list 1205.415 255.9961) 
(list 1205.415 255.8191) 
(list 1279.4375 255.4691)))
(apply 'command (append '("pline") coords '("c")))
(setq currobj (ssadd (entlast) currobj))
(setq coords (list 
(list 1279.4375 255.3261) 
(list 1205.415 255.6761) 
(list 1205.415 255.4991) 
(list 1279.4375 255.2491)))
(apply 'command (append '("pline") coords '("c")))
(setq currobj (ssadd (entlast) currobj))
(setq coords (list 
(list 1279.4375 255.1061) 
(list 1205.415 255.3561) 
(list 1205.415 255.1791) 
(list 1279.4375 255.0291)))
(apply 'command (append '("pline") coords '("c")))
(setq currobj (ssadd (entlast) currobj))
(setq coords (list 
(list 1279.4375 254.8861) 
(list 1205.415 255.0361) 
(list 1205.415 254.8591) 
(list 1279.4375 254.8091)))
(apply 'command (append '("pline") coords '("c")))
(setq currobj (ssadd (entlast) currobj))
(setq coords (list 
(list 1279.4375 254.6661) 
(list 1205.415 254.7161) 
(list 1205.415 254.5391) 
(list 1279.4375 254.5891)))
(apply 'command (append '("pline") coords '("c")))
(setq currobj (ssadd (entlast) currobj))
(setq coords (list 
(list 1279.4375 254.4461) 
(list 1205.415 254.3961) 
(list 1205.415 254.2191) 
(list 1279.4375 254.3691)))
(apply 'command (append '("pline") coords '("c")))
(setq currobj (ssadd (entlast) currobj))
(setq coords (list 
(list 1279.4375 254.2261) 
(list 1205.415 254.0761) 
(list 1205.415 253.8991) 
(list 1279.4375 254.1491)))
(apply 'command (append '("pline") coords '("c")))
(setq currobj (ssadd (entlast) currobj))
(setq coords (list 
(list 1279.4375 254.0061) 
(list 1205.415 253.7561) 
(list 1205.415 253.5791) 
(list 1279.4375 253.9291)))
(apply 'command (append '("pline") coords '("c")))
(setq currobj (ssadd (entlast) currobj))
(setq coords (list 
(list 1279.4375 253.7861) 
(list 1205.415 253.4361) 
(list 1205.415 253.2591) 
(list 1279.4375 253.7091)))
(apply 'command (append '("pline") coords '("c")))
(setq currobj (ssadd (entlast) currobj))
(setq coords (list 
(list 1279.4375 253.5661) 
(list 1205.415 253.1161) 
(list 1205.415 252.9391) 
(list 1279.4375 253.4891)))
(apply 'command (append '("pline") coords '("c")))
(setq currobj (ssadd (entlast) currobj))
(setq coords (list 
(list 1279.4375 253.3461) 
(list 1205.415 252.7961) 
(list 1205.415 252.6191) 
(list 1279.4375 253.2691)))
(apply 'command (append '("pline") coords '("c")))
(setq currobj (ssadd (entlast) currobj))
(setq coords (list 
(list 1279.4375 253.1261) 
(list 1205.415 252.4761) 
(list 1205.415 252.2991) 
(list 1279.4375 253.0491)))
(apply 'command (append '("pline") coords '("c")))
(setq currobj (ssadd (entlast) currobj))
(command "_layer" "set" "nitride" "")
(command "_layer" "set" "text" "")
(command "_circle" "1279.0625,241.9061" "0.075")
(command "_circle" "1279.0625,242.2061" "0.075")
(command "_circle" "1279.0625,242.5061" "0.075")
(command "_circle" "1279.0625,242.8061" "0.075")
(command "_circle" "1279.0625,243.1061" "0.075")
(command "_circle" "1278.7625,241.9061" "0.075")
(command "_circle" "1278.7625,242.2061" "0.075")
(command "_circle" "1278.7625,242.5061" "0.075")
(command "_circle" "1278.7625,242.8061" "0.075")
(command "_circle" "1278.7625,243.1061" "0.075")
(command "_circle" "1278.4625,241.9061" "0.075")
(command "_circle" "1278.4625,242.2061" "0.075")
(command "_circle" "1278.4625,242.5061" "0.075")
(command "_circle" "1278.4625,242.8061" "0.075")
(command "_circle" "1278.4625,243.1061" "0.075")
(command "_circle" "1278.1625,241.9061" "0.075")
(command "_circle" "1278.1625,242.2061" "0.075")
(command "_circle" "1278.1625,242.5061" "0.075")
(command "_circle" "1278.1625,242.8061" "0.075")
(command "_circle" "1278.1625,243.1061" "0.075")
(command "_circle" "1277.8625,241.9061" "0.075")
(command "_circle" "1277.8625,242.2061" "0.075")
(command "_circle" "1277.8625,242.5061" "0.075")
(command "_circle" "1277.8625,242.8061" "0.075")
(command "_circle" "1277.8625,243.1061" "0.075")
(command "_layer" "set" "nitride" "")
(setq coords (list 
(list 1280.2625 267.3491) 
(list 1280.2625 382.9939) 
(list 1279.7375 382.9939) 
(list 1279.7375 267.3491)))
(apply 'command (append '("pline") coords '("c")))
(setq currobj (ssadd (entlast) currobj))
(command "_layer" "set" "prebias" "")
(command "_rectangle" "1279.7375,267.3491" "1280.2625,382.9939")
(setq currobj (ssadd (entlast) currobj))
(command "_layer" "set" "nitride" "")
(setq coords (list 
(list 1280.2625 382.9939) 
(list 1280.5625 392.9939) 
(list 1280.5625 392.9939) 
(list 1280.5625 393.9939) 
(list 1354.585 393.2439) 
(list 1354.585 398.1869) 
(list 1280.5625 397.4369) 
(list 1280.5625 398.4369) 
(list 1280.5625 398.4369) 
(list 1280.2625 408.4369) 
(list 1279.7375 408.4369) 
(list 1279.4375 398.4369) 
(list 1279.4375 398.4369) 
(list 1279.4375 397.4369) 
(list 1205.415 398.1869) 
(list 1205.415 393.2439) 
(list 1279.4375 393.9939) 
(list 1279.4375 392.9939) 
(list 1279.4375 392.9939) 
(list 1279.7375 382.9939)))
(apply 'command (append '("pline") coords '("c")))
(setq currobj (ssadd (entlast) currobj))
(command "_layer" "set" "prebias" "")
(setq coords (list 
(list 1279.4375 382.9939) 
(list 1279.4375 393.9939) 
(list 1205.415 393.2439) 
(list 1205.415 398.1869) 
(list 1279.4375 397.4369) 
(list 1279.4375 408.4369) 
(list 1280.5625 408.4369) 
(list 1280.5625 397.4369) 
(list 1354.585 398.1869) 
(list 1354.585 393.2439) 
(list 1280.5625 393.9939) 
(list 1280.5625 382.9939)))
(apply 'command (append '("pline") coords '("c")))
(setq currobj (ssadd (entlast) currobj))
(command "_layer" "set" "nitride" "")
(command "_layer" "set" "fda1" "")
(setq coords (list 
(list 1280.5625 394.1369) 
(list 1354.585 393.3869) 
(list 1354.585 393.5639) 
(list 1280.5625 394.2139)))
(apply 'command (append '("pline") coords '("c")))
(setq currobj (ssadd (entlast) currobj))
(setq coords (list 
(list 1280.5625 394.3569) 
(list 1354.585 393.7069) 
(list 1354.585 393.8839) 
(list 1280.5625 394.4339)))
(apply 'command (append '("pline") coords '("c")))
(setq currobj (ssadd (entlast) currobj))
(setq coords (list 
(list 1280.5625 394.5769) 
(list 1354.585 394.0269) 
(list 1354.585 394.2039) 
(list 1280.5625 394.6539)))
(apply 'command (append '("pline") coords '("c")))
(setq currobj (ssadd (entlast) currobj))
(setq coords (list 
(list 1280.5625 394.7969) 
(list 1354.585 394.3469) 
(list 1354.585 394.5239) 
(list 1280.5625 394.8739)))
(apply 'command (append '("pline") coords '("c")))
(setq currobj (ssadd (entlast) currobj))
(setq coords (list 
(list 1280.5625 395.0169) 
(list 1354.585 394.6669) 
(list 1354.585 394.8439) 
(list 1280.5625 395.0939)))
(apply 'command (append '("pline") coords '("c")))
(setq currobj (ssadd (entlast) currobj))
(setq coords (list 
(list 1280.5625 395.2369) 
(list 1354.585 394.9869) 
(list 1354.585 395.1639) 
(list 1280.5625 395.3139)))
(apply 'command (append '("pline") coords '("c")))
(setq currobj (ssadd (entlast) currobj))
(setq coords (list 
(list 1280.5625 395.4569) 
(list 1354.585 395.3069) 
(list 1354.585 395.4839) 
(list 1280.5625 395.5339)))
(apply 'command (append '("pline") coords '("c")))
(setq currobj (ssadd (entlast) currobj))
(setq coords (list 
(list 1280.5625 395.6769) 
(list 1354.585 395.6269) 
(list 1354.585 395.8039) 
(list 1280.5625 395.7539)))
(apply 'command (append '("pline") coords '("c")))
(setq currobj (ssadd (entlast) currobj))
(setq coords (list 
(list 1280.5625 395.8969) 
(list 1354.585 395.9469) 
(list 1354.585 396.1239) 
(list 1280.5625 395.9739)))
(apply 'command (append '("pline") coords '("c")))
(setq currobj (ssadd (entlast) currobj))
(setq coords (list 
(list 1280.5625 396.1169) 
(list 1354.585 396.2669) 
(list 1354.585 396.4439) 
(list 1280.5625 396.1939)))
(apply 'command (append '("pline") coords '("c")))
(setq currobj (ssadd (entlast) currobj))
(setq coords (list 
(list 1280.5625 396.3369) 
(list 1354.585 396.5869) 
(list 1354.585 396.7639) 
(list 1280.5625 396.4139)))
(apply 'command (append '("pline") coords '("c")))
(setq currobj (ssadd (entlast) currobj))
(setq coords (list 
(list 1280.5625 396.5569) 
(list 1354.585 396.9069) 
(list 1354.585 397.0839) 
(list 1280.5625 396.6339)))
(apply 'command (append '("pline") coords '("c")))
(setq currobj (ssadd (entlast) currobj))
(setq coords (list 
(list 1280.5625 396.7769) 
(list 1354.585 397.2269) 
(list 1354.585 397.4039) 
(list 1280.5625 396.8539)))
(apply 'command (append '("pline") coords '("c")))
(setq currobj (ssadd (entlast) currobj))
(setq coords (list 
(list 1280.5625 396.9969) 
(list 1354.585 397.5469) 
(list 1354.585 397.7239) 
(list 1280.5625 397.0739)))
(apply 'command (append '("pline") coords '("c")))
(setq currobj (ssadd (entlast) currobj))
(setq coords (list 
(list 1280.5625 397.2169) 
(list 1354.585 397.8669) 
(list 1354.585 398.0439) 
(list 1280.5625 397.2939)))
(apply 'command (append '("pline") coords '("c")))
(setq currobj (ssadd (entlast) currobj))
(setq coords (list 
(list 1279.4375 397.2939) 
(list 1205.415 398.0439) 
(list 1205.415 397.8669) 
(list 1279.4375 397.2169)))
(apply 'command (append '("pline") coords '("c")))
(setq currobj (ssadd (entlast) currobj))
(setq coords (list 
(list 1279.4375 397.0739) 
(list 1205.415 397.7239) 
(list 1205.415 397.5469) 
(list 1279.4375 396.9969)))
(apply 'command (append '("pline") coords '("c")))
(setq currobj (ssadd (entlast) currobj))
(setq coords (list 
(list 1279.4375 396.8539) 
(list 1205.415 397.4039) 
(list 1205.415 397.2269) 
(list 1279.4375 396.7769)))
(apply 'command (append '("pline") coords '("c")))
(setq currobj (ssadd (entlast) currobj))
(setq coords (list 
(list 1279.4375 396.6339) 
(list 1205.415 397.0839) 
(list 1205.415 396.9069) 
(list 1279.4375 396.5569)))
(apply 'command (append '("pline") coords '("c")))
(setq currobj (ssadd (entlast) currobj))
(setq coords (list 
(list 1279.4375 396.4139) 
(list 1205.415 396.7639) 
(list 1205.415 396.5869) 
(list 1279.4375 396.3369)))
(apply 'command (append '("pline") coords '("c")))
(setq currobj (ssadd (entlast) currobj))
(setq coords (list 
(list 1279.4375 396.1939) 
(list 1205.415 396.4439) 
(list 1205.415 396.2669) 
(list 1279.4375 396.1169)))
(apply 'command (append '("pline") coords '("c")))
(setq currobj (ssadd (entlast) currobj))
(setq coords (list 
(list 1279.4375 395.9739) 
(list 1205.415 396.1239) 
(list 1205.415 395.9469) 
(list 1279.4375 395.8969)))
(apply 'command (append '("pline") coords '("c")))
(setq currobj (ssadd (entlast) currobj))
(setq coords (list 
(list 1279.4375 395.7539) 
(list 1205.415 395.8039) 
(list 1205.415 395.6269) 
(list 1279.4375 395.6769)))
(apply 'command (append '("pline") coords '("c")))
(setq currobj (ssadd (entlast) currobj))
(setq coords (list 
(list 1279.4375 395.5339) 
(list 1205.415 395.4839) 
(list 1205.415 395.3069) 
(list 1279.4375 395.4569)))
(apply 'command (append '("pline") coords '("c")))
(setq currobj (ssadd (entlast) currobj))
(setq coords (list 
(list 1279.4375 395.3139) 
(list 1205.415 395.1639) 
(list 1205.415 394.9869) 
(list 1279.4375 395.2369)))
(apply 'command (append '("pline") coords '("c")))
(setq currobj (ssadd (entlast) currobj))
(setq coords (list 
(list 1279.4375 395.0939) 
(list 1205.415 394.8439) 
(list 1205.415 394.6669) 
(list 1279.4375 395.0169)))
(apply 'command (append '("pline") coords '("c")))
(setq currobj (ssadd (entlast) currobj))
(setq coords (list 
(list 1279.4375 394.8739) 
(list 1205.415 394.5239) 
(list 1205.415 394.3469) 
(list 1279.4375 394.7969)))
(apply 'command (append '("pline") coords '("c")))
(setq currobj (ssadd (entlast) currobj))
(setq coords (list 
(list 1279.4375 394.6539) 
(list 1205.415 394.2039) 
(list 1205.415 394.0269) 
(list 1279.4375 394.5769)))
(apply 'command (append '("pline") coords '("c")))
(setq currobj (ssadd (entlast) currobj))
(setq coords (list 
(list 1279.4375 394.4339) 
(list 1205.415 393.8839) 
(list 1205.415 393.7069) 
(list 1279.4375 394.3569)))
(apply 'command (append '("pline") coords '("c")))
(setq currobj (ssadd (entlast) currobj))
(setq coords (list 
(list 1279.4375 394.2139) 
(list 1205.415 393.5639) 
(list 1205.415 393.3869) 
(list 1279.4375 394.1369)))
(apply 'command (append '("pline") coords '("c")))
(setq currobj (ssadd (entlast) currobj))
(command "_layer" "set" "nitride" "")
(command "_layer" "set" "text" "")
(command "_circle" "1279.0625,382.9939" "0.075")
(command "_circle" "1279.0625,383.2939" "0.075")
(command "_circle" "1279.0625,383.5939" "0.075")
(command "_circle" "1279.0625,383.8939" "0.075")
(command "_circle" "1279.0625,384.1939" "0.075")
(command "_circle" "1278.7625,382.9939" "0.075")
(command "_circle" "1278.7625,383.2939" "0.075")
(command "_circle" "1278.7625,383.5939" "0.075")
(command "_circle" "1278.7625,383.8939" "0.075")
(command "_circle" "1278.7625,384.1939" "0.075")
(command "_circle" "1278.4625,382.9939" "0.075")
(command "_circle" "1278.4625,383.2939" "0.075")
(command "_circle" "1278.4625,383.5939" "0.075")
(command "_circle" "1278.4625,383.8939" "0.075")
(command "_circle" "1278.4625,384.1939" "0.075")
(command "_circle" "1278.1625,382.9939" "0.075")
(command "_circle" "1278.1625,383.2939" "0.075")
(command "_circle" "1278.1625,383.5939" "0.075")
(command "_circle" "1278.1625,383.8939" "0.075")
(command "_circle" "1278.1625,384.1939" "0.075")
(command "_circle" "1277.8625,382.9939" "0.075")
(command "_circle" "1277.8625,383.2939" "0.075")
(command "_circle" "1277.8625,383.5939" "0.075")
(command "_circle" "1277.8625,383.8939" "0.075")
(command "_circle" "1277.8625,384.1939" "0.075")
(command "_layer" "set" "nitride" "")
(setq coords (list 
(list 1280.2625 408.4369) 
(list 1280.2625 524.0816) 
(list 1279.7375 524.0816) 
(list 1279.7375 408.4369)))
(apply 'command (append '("pline") coords '("c")))
(setq currobj (ssadd (entlast) currobj))
(command "_layer" "set" "prebias" "")
(command "_rectangle" "1279.7375,408.4369" "1280.2625,524.0816")
(setq currobj (ssadd (entlast) currobj))
(command "_layer" "set" "nitride" "")
(setq coords (list 
(list 1280.2625 524.0816) 
(list 1280.5625 534.0816) 
(list 1280.5625 534.0816) 
(list 1280.5625 535.0816) 
(list 1354.585 534.3316) 
(list 1354.585 539.2746) 
(list 1280.5625 538.5246) 
(list 1280.5625 539.5246) 
(list 1280.5625 539.5246) 
(list 1280.2625 549.5246) 
(list 1279.7375 549.5246) 
(list 1279.4375 539.5246) 
(list 1279.4375 539.5246) 
(list 1279.4375 538.5246) 
(list 1205.415 539.2746) 
(list 1205.415 534.3316) 
(list 1279.4375 535.0816) 
(list 1279.4375 534.0816) 
(list 1279.4375 534.0816) 
(list 1279.7375 524.0816)))
(apply 'command (append '("pline") coords '("c")))
(setq currobj (ssadd (entlast) currobj))
(command "_layer" "set" "prebias" "")
(setq coords (list 
(list 1279.4375 524.0816) 
(list 1279.4375 535.0816) 
(list 1205.415 534.3316) 
(list 1205.415 539.2746) 
(list 1279.4375 538.5246) 
(list 1279.4375 549.5246) 
(list 1280.5625 549.5246) 
(list 1280.5625 538.5246) 
(list 1354.585 539.2746) 
(list 1354.585 534.3316) 
(list 1280.5625 535.0816) 
(list 1280.5625 524.0816)))
(apply 'command (append '("pline") coords '("c")))
(setq currobj (ssadd (entlast) currobj))
(command "_layer" "set" "nitride" "")
(command "_layer" "set" "fda1" "")
(setq coords (list 
(list 1280.5625 535.2246) 
(list 1354.585 534.4746) 
(list 1354.585 534.6516) 
(list 1280.5625 535.3016)))
(apply 'command (append '("pline") coords '("c")))
(setq currobj (ssadd (entlast) currobj))
(setq coords (list 
(list 1280.5625 535.4446) 
(list 1354.585 534.7946) 
(list 1354.585 534.9716) 
(list 1280.5625 535.5216)))
(apply 'command (append '("pline") coords '("c")))
(setq currobj (ssadd (entlast) currobj))
(setq coords (list 
(list 1280.5625 535.6646) 
(list 1354.585 535.1146) 
(list 1354.585 535.2916) 
(list 1280.5625 535.7416)))
(apply 'command (append '("pline") coords '("c")))
(setq currobj (ssadd (entlast) currobj))
(setq coords (list 
(list 1280.5625 535.8846) 
(list 1354.585 535.4346) 
(list 1354.585 535.6116) 
(list 1280.5625 535.9616)))
(apply 'command (append '("pline") coords '("c")))
(setq currobj (ssadd (entlast) currobj))
(setq coords (list 
(list 1280.5625 536.1046) 
(list 1354.585 535.7546) 
(list 1354.585 535.9316) 
(list 1280.5625 536.1816)))
(apply 'command (append '("pline") coords '("c")))
(setq currobj (ssadd (entlast) currobj))
(setq coords (list 
(list 1280.5625 536.3246) 
(list 1354.585 536.0746) 
(list 1354.585 536.2516) 
(list 1280.5625 536.4016)))
(apply 'command (append '("pline") coords '("c")))
(setq currobj (ssadd (entlast) currobj))
(setq coords (list 
(list 1280.5625 536.5446) 
(list 1354.585 536.3946) 
(list 1354.585 536.5716) 
(list 1280.5625 536.6216)))
(apply 'command (append '("pline") coords '("c")))
(setq currobj (ssadd (entlast) currobj))
(setq coords (list 
(list 1280.5625 536.7646) 
(list 1354.585 536.7146) 
(list 1354.585 536.8916) 
(list 1280.5625 536.8416)))
(apply 'command (append '("pline") coords '("c")))
(setq currobj (ssadd (entlast) currobj))
(setq coords (list 
(list 1280.5625 536.9846) 
(list 1354.585 537.0346) 
(list 1354.585 537.2116) 
(list 1280.5625 537.0616)))
(apply 'command (append '("pline") coords '("c")))
(setq currobj (ssadd (entlast) currobj))
(setq coords (list 
(list 1280.5625 537.2046) 
(list 1354.585 537.3546) 
(list 1354.585 537.5316) 
(list 1280.5625 537.2816)))
(apply 'command (append '("pline") coords '("c")))
(setq currobj (ssadd (entlast) currobj))
(setq coords (list 
(list 1280.5625 537.4246) 
(list 1354.585 537.6746) 
(list 1354.585 537.8516) 
(list 1280.5625 537.5016)))
(apply 'command (append '("pline") coords '("c")))
(setq currobj (ssadd (entlast) currobj))
(setq coords (list 
(list 1280.5625 537.6446) 
(list 1354.585 537.9946) 
(list 1354.585 538.1716) 
(list 1280.5625 537.7216)))
(apply 'command (append '("pline") coords '("c")))
(setq currobj (ssadd (entlast) currobj))
(setq coords (list 
(list 1280.5625 537.8646) 
(list 1354.585 538.3146) 
(list 1354.585 538.4916) 
(list 1280.5625 537.9416)))
(apply 'command (append '("pline") coords '("c")))
(setq currobj (ssadd (entlast) currobj))
(setq coords (list 
(list 1280.5625 538.0846) 
(list 1354.585 538.6346) 
(list 1354.585 538.8116) 
(list 1280.5625 538.1616)))
(apply 'command (append '("pline") coords '("c")))
(setq currobj (ssadd (entlast) currobj))
(setq coords (list 
(list 1280.5625 538.3046) 
(list 1354.585 538.9546) 
(list 1354.585 539.1316) 
(list 1280.5625 538.3816)))
(apply 'command (append '("pline") coords '("c")))
(setq currobj (ssadd (entlast) currobj))
(setq coords (list 
(list 1279.4375 538.3816) 
(list 1205.415 539.1316) 
(list 1205.415 538.9546) 
(list 1279.4375 538.3046)))
(apply 'command (append '("pline") coords '("c")))
(setq currobj (ssadd (entlast) currobj))
(setq coords (list 
(list 1279.4375 538.1616) 
(list 1205.415 538.8116) 
(list 1205.415 538.6346) 
(list 1279.4375 538.0846)))
(apply 'command (append '("pline") coords '("c")))
(setq currobj (ssadd (entlast) currobj))
(setq coords (list 
(list 1279.4375 537.9416) 
(list 1205.415 538.4916) 
(list 1205.415 538.3146) 
(list 1279.4375 537.8646)))
(apply 'command (append '("pline") coords '("c")))
(setq currobj (ssadd (entlast) currobj))
(setq coords (list 
(list 1279.4375 537.7216) 
(list 1205.415 538.1716) 
(list 1205.415 537.9946) 
(list 1279.4375 537.6446)))
(apply 'command (append '("pline") coords '("c")))
(setq currobj (ssadd (entlast) currobj))
(setq coords (list 
(list 1279.4375 537.5016) 
(list 1205.415 537.8516) 
(list 1205.415 537.6746) 
(list 1279.4375 537.4246)))
(apply 'command (append '("pline") coords '("c")))
(setq currobj (ssadd (entlast) currobj))
(setq coords (list 
(list 1279.4375 537.2816) 
(list 1205.415 537.5316) 
(list 1205.415 537.3546) 
(list 1279.4375 537.2046)))
(apply 'command (append '("pline") coords '("c")))
(setq currobj (ssadd (entlast) currobj))
(setq coords (list 
(list 1279.4375 537.0616) 
(list 1205.415 537.2116) 
(list 1205.415 537.0346) 
(list 1279.4375 536.9846)))
(apply 'command (append '("pline") coords '("c")))
(setq currobj (ssadd (entlast) currobj))
(setq coords (list 
(list 1279.4375 536.8416) 
(list 1205.415 536.8916) 
(list 1205.415 536.7146) 
(list 1279.4375 536.7646)))
(apply 'command (append '("pline") coords '("c")))
(setq currobj (ssadd (entlast) currobj))
(setq coords (list 
(list 1279.4375 536.6216) 
(list 1205.415 536.5716) 
(list 1205.415 536.3946) 
(list 1279.4375 536.5446)))
(apply 'command (append '("pline") coords '("c")))
(setq currobj (ssadd (entlast) currobj))
(setq coords (list 
(list 1279.4375 536.4016) 
(list 1205.415 536.2516) 
(list 1205.415 536.0746) 
(list 1279.4375 536.3246)))
(apply 'command (append '("pline") coords '("c")))
(setq currobj (ssadd (entlast) currobj))
(setq coords (list 
(list 1279.4375 536.1816) 
(list 1205.415 535.9316) 
(list 1205.415 535.7546) 
(list 1279.4375 536.1046)))
(apply 'command (append '("pline") coords '("c")))
(setq currobj (ssadd (entlast) currobj))
(setq coords (list 
(list 1279.4375 535.9616) 
(list 1205.415 535.6116) 
(list 1205.415 535.4346) 
(list 1279.4375 535.8846)))
(apply 'command (append '("pline") coords '("c")))
(setq currobj (ssadd (entlast) currobj))
(setq coords (list 
(list 1279.4375 535.7416) 
(list 1205.415 535.2916) 
(list 1205.415 535.1146) 
(list 1279.4375 535.6646)))
(apply 'command (append '("pline") coords '("c")))
(setq currobj (ssadd (entlast) currobj))
(setq coords (list 
(list 1279.4375 535.5216) 
(list 1205.415 534.9716) 
(list 1205.415 534.7946) 
(list 1279.4375 535.4446)))
(apply 'command (append '("pline") coords '("c")))
(setq currobj (ssadd (entlast) currobj))
(setq coords (list 
(list 1279.4375 535.3016) 
(list 1205.415 534.6516) 
(list 1205.415 534.4746) 
(list 1279.4375 535.2246)))
(apply 'command (append '("pline") coords '("c")))
(setq currobj (ssadd (entlast) currobj))
(command "_layer" "set" "nitride" "")
(command "_layer" "set" "text" "")
(command "_circle" "1279.0625,524.0816" "0.075")
(command "_circle" "1279.0625,524.3816" "0.075")
(command "_circle" "1279.0625,524.6816" "0.075")
(command "_circle" "1279.0625,524.9816" "0.075")
(command "_circle" "1279.0625,525.2816" "0.075")
(command "_circle" "1278.7625,524.0816" "0.075")
(command "_circle" "1278.7625,524.3816" "0.075")
(command "_circle" "1278.7625,524.6816" "0.075")
(command "_circle" "1278.7625,524.9816" "0.075")
(command "_circle" "1278.7625,525.2816" "0.075")
(command "_circle" "1278.4625,524.0816" "0.075")
(command "_circle" "1278.4625,524.3816" "0.075")
(command "_circle" "1278.4625,524.6816" "0.075")
(command "_circle" "1278.4625,524.9816" "0.075")
(command "_circle" "1278.4625,525.2816" "0.075")
(command "_circle" "1278.1625,524.0816" "0.075")
(command "_circle" "1278.1625,524.3816" "0.075")
(command "_circle" "1278.1625,524.6816" "0.075")
(command "_circle" "1278.1625,524.9816" "0.075")
(command "_circle" "1278.1625,525.2816" "0.075")
(command "_circle" "1277.8625,524.0816" "0.075")
(command "_circle" "1277.8625,524.3816" "0.075")
(command "_circle" "1277.8625,524.6816" "0.075")
(command "_circle" "1277.8625,524.9816" "0.075")
(command "_circle" "1277.8625,525.2816" "0.075")
(command "_layer" "set" "nitride" "")
(setq coords (list 
(list 1280.2625 549.5246) 
(list 1280.2625 665.1693) 
(list 1279.7375 665.1693) 
(list 1279.7375 549.5246)))
(apply 'command (append '("pline") coords '("c")))
(setq currobj (ssadd (entlast) currobj))
(command "_layer" "set" "prebias" "")
(command "_rectangle" "1279.7375,549.5246" "1280.2625,665.1693")
(setq currobj (ssadd (entlast) currobj))
(command "_layer" "set" "nitride" "")
(setq coords (list 
(list 1280.2625 665.1693) 
(list 1280.5625 675.1693) 
(list 1280.5625 675.1693) 
(list 1280.5625 676.1693) 
(list 1354.585 675.4193) 
(list 1354.585 680.3623) 
(list 1280.5625 679.6123) 
(list 1280.5625 680.6123) 
(list 1280.5625 680.6123) 
(list 1280.2625 690.6123) 
(list 1279.7375 690.6123) 
(list 1279.4375 680.6123) 
(list 1279.4375 680.6123) 
(list 1279.4375 679.6123) 
(list 1205.415 680.3623) 
(list 1205.415 675.4193) 
(list 1279.4375 676.1693) 
(list 1279.4375 675.1693) 
(list 1279.4375 675.1693) 
(list 1279.7375 665.1693)))
(apply 'command (append '("pline") coords '("c")))
(setq currobj (ssadd (entlast) currobj))
(command "_layer" "set" "prebias" "")
(setq coords (list 
(list 1279.4375 665.1693) 
(list 1279.4375 676.1693) 
(list 1205.415 675.4193) 
(list 1205.415 680.3623) 
(list 1279.4375 679.6123) 
(list 1279.4375 690.6123) 
(list 1280.5625 690.6123) 
(list 1280.5625 679.6123) 
(list 1354.585 680.3623) 
(list 1354.585 675.4193) 
(list 1280.5625 676.1693) 
(list 1280.5625 665.1693)))
(apply 'command (append '("pline") coords '("c")))
(setq currobj (ssadd (entlast) currobj))
(command "_layer" "set" "nitride" "")
(command "_layer" "set" "fda1" "")
(setq coords (list 
(list 1280.5625 676.3123) 
(list 1354.585 675.5623) 
(list 1354.585 675.7393) 
(list 1280.5625 676.3893)))
(apply 'command (append '("pline") coords '("c")))
(setq currobj (ssadd (entlast) currobj))
(setq coords (list 
(list 1280.5625 676.5323) 
(list 1354.585 675.8823) 
(list 1354.585 676.0593) 
(list 1280.5625 676.6093)))
(apply 'command (append '("pline") coords '("c")))
(setq currobj (ssadd (entlast) currobj))
(setq coords (list 
(list 1280.5625 676.7523) 
(list 1354.585 676.2023) 
(list 1354.585 676.3793) 
(list 1280.5625 676.8293)))
(apply 'command (append '("pline") coords '("c")))
(setq currobj (ssadd (entlast) currobj))
(setq coords (list 
(list 1280.5625 676.9723) 
(list 1354.585 676.5223) 
(list 1354.585 676.6993) 
(list 1280.5625 677.0493)))
(apply 'command (append '("pline") coords '("c")))
(setq currobj (ssadd (entlast) currobj))
(setq coords (list 
(list 1280.5625 677.1923) 
(list 1354.585 676.8423) 
(list 1354.585 677.0193) 
(list 1280.5625 677.2693)))
(apply 'command (append '("pline") coords '("c")))
(setq currobj (ssadd (entlast) currobj))
(setq coords (list 
(list 1280.5625 677.4123) 
(list 1354.585 677.1623) 
(list 1354.585 677.3393) 
(list 1280.5625 677.4893)))
(apply 'command (append '("pline") coords '("c")))
(setq currobj (ssadd (entlast) currobj))
(setq coords (list 
(list 1280.5625 677.6323) 
(list 1354.585 677.4823) 
(list 1354.585 677.6593) 
(list 1280.5625 677.7093)))
(apply 'command (append '("pline") coords '("c")))
(setq currobj (ssadd (entlast) currobj))
(setq coords (list 
(list 1280.5625 677.8523) 
(list 1354.585 677.8023) 
(list 1354.585 677.9793) 
(list 1280.5625 677.9293)))
(apply 'command (append '("pline") coords '("c")))
(setq currobj (ssadd (entlast) currobj))
(setq coords (list 
(list 1280.5625 678.0723) 
(list 1354.585 678.1223) 
(list 1354.585 678.2993) 
(list 1280.5625 678.1493)))
(apply 'command (append '("pline") coords '("c")))
(setq currobj (ssadd (entlast) currobj))
(setq coords (list 
(list 1280.5625 678.2923) 
(list 1354.585 678.4423) 
(list 1354.585 678.6193) 
(list 1280.5625 678.3693)))
(apply 'command (append '("pline") coords '("c")))
(setq currobj (ssadd (entlast) currobj))
(setq coords (list 
(list 1280.5625 678.5123) 
(list 1354.585 678.7623) 
(list 1354.585 678.9393) 
(list 1280.5625 678.5893)))
(apply 'command (append '("pline") coords '("c")))
(setq currobj (ssadd (entlast) currobj))
(setq coords (list 
(list 1280.5625 678.7323) 
(list 1354.585 679.0823) 
(list 1354.585 679.2593) 
(list 1280.5625 678.8093)))
(apply 'command (append '("pline") coords '("c")))
(setq currobj (ssadd (entlast) currobj))
(setq coords (list 
(list 1280.5625 678.9523) 
(list 1354.585 679.4023) 
(list 1354.585 679.5793) 
(list 1280.5625 679.0293)))
(apply 'command (append '("pline") coords '("c")))
(setq currobj (ssadd (entlast) currobj))
(setq coords (list 
(list 1280.5625 679.1723) 
(list 1354.585 679.7223) 
(list 1354.585 679.8993) 
(list 1280.5625 679.2493)))
(apply 'command (append '("pline") coords '("c")))
(setq currobj (ssadd (entlast) currobj))
(setq coords (list 
(list 1280.5625 679.3923) 
(list 1354.585 680.0423) 
(list 1354.585 680.2193) 
(list 1280.5625 679.4693)))
(apply 'command (append '("pline") coords '("c")))
(setq currobj (ssadd (entlast) currobj))
(setq coords (list 
(list 1279.4375 679.4693) 
(list 1205.415 680.2193) 
(list 1205.415 680.0423) 
(list 1279.4375 679.3923)))
(apply 'command (append '("pline") coords '("c")))
(setq currobj (ssadd (entlast) currobj))
(setq coords (list 
(list 1279.4375 679.2493) 
(list 1205.415 679.8993) 
(list 1205.415 679.7223) 
(list 1279.4375 679.1723)))
(apply 'command (append '("pline") coords '("c")))
(setq currobj (ssadd (entlast) currobj))
(setq coords (list 
(list 1279.4375 679.0293) 
(list 1205.415 679.5793) 
(list 1205.415 679.4023) 
(list 1279.4375 678.9523)))
(apply 'command (append '("pline") coords '("c")))
(setq currobj (ssadd (entlast) currobj))
(setq coords (list 
(list 1279.4375 678.8093) 
(list 1205.415 679.2593) 
(list 1205.415 679.0823) 
(list 1279.4375 678.7323)))
(apply 'command (append '("pline") coords '("c")))
(setq currobj (ssadd (entlast) currobj))
(setq coords (list 
(list 1279.4375 678.5893) 
(list 1205.415 678.9393) 
(list 1205.415 678.7623) 
(list 1279.4375 678.5123)))
(apply 'command (append '("pline") coords '("c")))
(setq currobj (ssadd (entlast) currobj))
(setq coords (list 
(list 1279.4375 678.3693) 
(list 1205.415 678.6193) 
(list 1205.415 678.4423) 
(list 1279.4375 678.2923)))
(apply 'command (append '("pline") coords '("c")))
(setq currobj (ssadd (entlast) currobj))
(setq coords (list 
(list 1279.4375 678.1493) 
(list 1205.415 678.2993) 
(list 1205.415 678.1223) 
(list 1279.4375 678.0723)))
(apply 'command (append '("pline") coords '("c")))
(setq currobj (ssadd (entlast) currobj))
(setq coords (list 
(list 1279.4375 677.9293) 
(list 1205.415 677.9793) 
(list 1205.415 677.8023) 
(list 1279.4375 677.8523)))
(apply 'command (append '("pline") coords '("c")))
(setq currobj (ssadd (entlast) currobj))
(setq coords (list 
(list 1279.4375 677.7093) 
(list 1205.415 677.6593) 
(list 1205.415 677.4823) 
(list 1279.4375 677.6323)))
(apply 'command (append '("pline") coords '("c")))
(setq currobj (ssadd (entlast) currobj))
(setq coords (list 
(list 1279.4375 677.4893) 
(list 1205.415 677.3393) 
(list 1205.415 677.1623) 
(list 1279.4375 677.4123)))
(apply 'command (append '("pline") coords '("c")))
(setq currobj (ssadd (entlast) currobj))
(setq coords (list 
(list 1279.4375 677.2693) 
(list 1205.415 677.0193) 
(list 1205.415 676.8423) 
(list 1279.4375 677.1923)))
(apply 'command (append '("pline") coords '("c")))
(setq currobj (ssadd (entlast) currobj))
(setq coords (list 
(list 1279.4375 677.0493) 
(list 1205.415 676.6993) 
(list 1205.415 676.5223) 
(list 1279.4375 676.9723)))
(apply 'command (append '("pline") coords '("c")))
(setq currobj (ssadd (entlast) currobj))
(setq coords (list 
(list 1279.4375 676.8293) 
(list 1205.415 676.3793) 
(list 1205.415 676.2023) 
(list 1279.4375 676.7523)))
(apply 'command (append '("pline") coords '("c")))
(setq currobj (ssadd (entlast) currobj))
(setq coords (list 
(list 1279.4375 676.6093) 
(list 1205.415 676.0593) 
(list 1205.415 675.8823) 
(list 1279.4375 676.5323)))
(apply 'command (append '("pline") coords '("c")))
(setq currobj (ssadd (entlast) currobj))
(setq coords (list 
(list 1279.4375 676.3893) 
(list 1205.415 675.7393) 
(list 1205.415 675.5623) 
(list 1279.4375 676.3123)))
(apply 'command (append '("pline") coords '("c")))
(setq currobj (ssadd (entlast) currobj))
(command "_layer" "set" "nitride" "")
(command "_layer" "set" "text" "")
(command "_circle" "1279.0625,665.1693" "0.075")
(command "_circle" "1279.0625,665.4693" "0.075")
(command "_circle" "1279.0625,665.7693" "0.075")
(command "_circle" "1279.0625,666.0693" "0.075")
(command "_circle" "1279.0625,666.3693" "0.075")
(command "_circle" "1278.7625,665.1693" "0.075")
(command "_circle" "1278.7625,665.4693" "0.075")
(command "_circle" "1278.7625,665.7693" "0.075")
(command "_circle" "1278.7625,666.0693" "0.075")
(command "_circle" "1278.7625,666.3693" "0.075")
(command "_circle" "1278.4625,665.1693" "0.075")
(command "_circle" "1278.4625,665.4693" "0.075")
(command "_circle" "1278.4625,665.7693" "0.075")
(command "_circle" "1278.4625,666.0693" "0.075")
(command "_circle" "1278.4625,666.3693" "0.075")
(command "_circle" "1278.1625,665.1693" "0.075")
(command "_circle" "1278.1625,665.4693" "0.075")
(command "_circle" "1278.1625,665.7693" "0.075")
(command "_circle" "1278.1625,666.0693" "0.075")
(command "_circle" "1278.1625,666.3693" "0.075")
(command "_circle" "1277.8625,665.1693" "0.075")
(command "_circle" "1277.8625,665.4693" "0.075")
(command "_circle" "1277.8625,665.7693" "0.075")
(command "_circle" "1277.8625,666.0693" "0.075")
(command "_circle" "1277.8625,666.3693" "0.075")
(command "_layer" "set" "nitride" "")
(setq coords (list 
(list 1280.2625 690.6123) 
(list 1280.2625 806.257) 
(list 1279.7375 806.257) 
(list 1279.7375 690.6123)))
(apply 'command (append '("pline") coords '("c")))
(setq currobj (ssadd (entlast) currobj))
(command "_layer" "set" "prebias" "")
(command "_rectangle" "1279.7375,690.6123" "1280.2625,806.257")
(setq currobj (ssadd (entlast) currobj))
(command "_layer" "set" "nitride" "")
(setq coords (list 
(list 1280.2625 806.257) 
(list 1280.5625 816.257) 
(list 1280.5625 816.257) 
(list 1280.5625 817.257) 
(list 1354.585 816.507) 
(list 1354.585 821.45) 
(list 1280.5625 820.7) 
(list 1280.5625 821.7) 
(list 1280.5625 821.7) 
(list 1280.2625 831.7) 
(list 1279.7375 831.7) 
(list 1279.4375 821.7) 
(list 1279.4375 821.7) 
(list 1279.4375 820.7) 
(list 1205.415 821.45) 
(list 1205.415 816.507) 
(list 1279.4375 817.257) 
(list 1279.4375 816.257) 
(list 1279.4375 816.257) 
(list 1279.7375 806.257)))
(apply 'command (append '("pline") coords '("c")))
(setq currobj (ssadd (entlast) currobj))
(command "_layer" "set" "prebias" "")
(setq coords (list 
(list 1279.4375 806.257) 
(list 1279.4375 817.257) 
(list 1205.415 816.507) 
(list 1205.415 821.45) 
(list 1279.4375 820.7) 
(list 1279.4375 831.7) 
(list 1280.5625 831.7) 
(list 1280.5625 820.7) 
(list 1354.585 821.45) 
(list 1354.585 816.507) 
(list 1280.5625 817.257) 
(list 1280.5625 806.257)))
(apply 'command (append '("pline") coords '("c")))
(setq currobj (ssadd (entlast) currobj))
(command "_layer" "set" "nitride" "")
(command "_layer" "set" "fda1" "")
(setq coords (list 
(list 1280.5625 817.4) 
(list 1354.585 816.65) 
(list 1354.585 816.827) 
(list 1280.5625 817.477)))
(apply 'command (append '("pline") coords '("c")))
(setq currobj (ssadd (entlast) currobj))
(setq coords (list 
(list 1280.5625 817.62) 
(list 1354.585 816.97) 
(list 1354.585 817.147) 
(list 1280.5625 817.697)))
(apply 'command (append '("pline") coords '("c")))
(setq currobj (ssadd (entlast) currobj))
(setq coords (list 
(list 1280.5625 817.84) 
(list 1354.585 817.29) 
(list 1354.585 817.467) 
(list 1280.5625 817.917)))
(apply 'command (append '("pline") coords '("c")))
(setq currobj (ssadd (entlast) currobj))
(setq coords (list 
(list 1280.5625 818.06) 
(list 1354.585 817.61) 
(list 1354.585 817.787) 
(list 1280.5625 818.137)))
(apply 'command (append '("pline") coords '("c")))
(setq currobj (ssadd (entlast) currobj))
(setq coords (list 
(list 1280.5625 818.28) 
(list 1354.585 817.93) 
(list 1354.585 818.107) 
(list 1280.5625 818.357)))
(apply 'command (append '("pline") coords '("c")))
(setq currobj (ssadd (entlast) currobj))
(setq coords (list 
(list 1280.5625 818.5) 
(list 1354.585 818.25) 
(list 1354.585 818.427) 
(list 1280.5625 818.577)))
(apply 'command (append '("pline") coords '("c")))
(setq currobj (ssadd (entlast) currobj))
(setq coords (list 
(list 1280.5625 818.72) 
(list 1354.585 818.57) 
(list 1354.585 818.747) 
(list 1280.5625 818.797)))
(apply 'command (append '("pline") coords '("c")))
(setq currobj (ssadd (entlast) currobj))
(setq coords (list 
(list 1280.5625 818.94) 
(list 1354.585 818.89) 
(list 1354.585 819.067) 
(list 1280.5625 819.017)))
(apply 'command (append '("pline") coords '("c")))
(setq currobj (ssadd (entlast) currobj))
(setq coords (list 
(list 1280.5625 819.16) 
(list 1354.585 819.21) 
(list 1354.585 819.387) 
(list 1280.5625 819.237)))
(apply 'command (append '("pline") coords '("c")))
(setq currobj (ssadd (entlast) currobj))
(setq coords (list 
(list 1280.5625 819.38) 
(list 1354.585 819.53) 
(list 1354.585 819.707) 
(list 1280.5625 819.457)))
(apply 'command (append '("pline") coords '("c")))
(setq currobj (ssadd (entlast) currobj))
(setq coords (list 
(list 1280.5625 819.6) 
(list 1354.585 819.85) 
(list 1354.585 820.027) 
(list 1280.5625 819.677)))
(apply 'command (append '("pline") coords '("c")))
(setq currobj (ssadd (entlast) currobj))
(setq coords (list 
(list 1280.5625 819.82) 
(list 1354.585 820.17) 
(list 1354.585 820.347) 
(list 1280.5625 819.897)))
(apply 'command (append '("pline") coords '("c")))
(setq currobj (ssadd (entlast) currobj))
(setq coords (list 
(list 1280.5625 820.04) 
(list 1354.585 820.49) 
(list 1354.585 820.667) 
(list 1280.5625 820.117)))
(apply 'command (append '("pline") coords '("c")))
(setq currobj (ssadd (entlast) currobj))
(setq coords (list 
(list 1280.5625 820.26) 
(list 1354.585 820.81) 
(list 1354.585 820.987) 
(list 1280.5625 820.337)))
(apply 'command (append '("pline") coords '("c")))
(setq currobj (ssadd (entlast) currobj))
(setq coords (list 
(list 1280.5625 820.48) 
(list 1354.585 821.13) 
(list 1354.585 821.307) 
(list 1280.5625 820.557)))
(apply 'command (append '("pline") coords '("c")))
(setq currobj (ssadd (entlast) currobj))
(setq coords (list 
(list 1279.4375 820.557) 
(list 1205.415 821.307) 
(list 1205.415 821.13) 
(list 1279.4375 820.48)))
(apply 'command (append '("pline") coords '("c")))
(setq currobj (ssadd (entlast) currobj))
(setq coords (list 
(list 1279.4375 820.337) 
(list 1205.415 820.987) 
(list 1205.415 820.81) 
(list 1279.4375 820.26)))
(apply 'command (append '("pline") coords '("c")))
(setq currobj (ssadd (entlast) currobj))
(setq coords (list 
(list 1279.4375 820.117) 
(list 1205.415 820.667) 
(list 1205.415 820.49) 
(list 1279.4375 820.04)))
(apply 'command (append '("pline") coords '("c")))
(setq currobj (ssadd (entlast) currobj))
(setq coords (list 
(list 1279.4375 819.897) 
(list 1205.415 820.347) 
(list 1205.415 820.17) 
(list 1279.4375 819.82)))
(apply 'command (append '("pline") coords '("c")))
(setq currobj (ssadd (entlast) currobj))
(setq coords (list 
(list 1279.4375 819.677) 
(list 1205.415 820.027) 
(list 1205.415 819.85) 
(list 1279.4375 819.6)))
(apply 'command (append '("pline") coords '("c")))
(setq currobj (ssadd (entlast) currobj))
(setq coords (list 
(list 1279.4375 819.457) 
(list 1205.415 819.707) 
(list 1205.415 819.53) 
(list 1279.4375 819.38)))
(apply 'command (append '("pline") coords '("c")))
(setq currobj (ssadd (entlast) currobj))
(setq coords (list 
(list 1279.4375 819.237) 
(list 1205.415 819.387) 
(list 1205.415 819.21) 
(list 1279.4375 819.16)))
(apply 'command (append '("pline") coords '("c")))
(setq currobj (ssadd (entlast) currobj))
(setq coords (list 
(list 1279.4375 819.017) 
(list 1205.415 819.067) 
(list 1205.415 818.89) 
(list 1279.4375 818.94)))
(apply 'command (append '("pline") coords '("c")))
(setq currobj (ssadd (entlast) currobj))
(setq coords (list 
(list 1279.4375 818.797) 
(list 1205.415 818.747) 
(list 1205.415 818.57) 
(list 1279.4375 818.72)))
(apply 'command (append '("pline") coords '("c")))
(setq currobj (ssadd (entlast) currobj))
(setq coords (list 
(list 1279.4375 818.577) 
(list 1205.415 818.427) 
(list 1205.415 818.25) 
(list 1279.4375 818.5)))
(apply 'command (append '("pline") coords '("c")))
(setq currobj (ssadd (entlast) currobj))
(setq coords (list 
(list 1279.4375 818.357) 
(list 1205.415 818.107) 
(list 1205.415 817.93) 
(list 1279.4375 818.28)))
(apply 'command (append '("pline") coords '("c")))
(setq currobj (ssadd (entlast) currobj))
(setq coords (list 
(list 1279.4375 818.137) 
(list 1205.415 817.787) 
(list 1205.415 817.61) 
(list 1279.4375 818.06)))
(apply 'command (append '("pline") coords '("c")))
(setq currobj (ssadd (entlast) currobj))
(setq coords (list 
(list 1279.4375 817.917) 
(list 1205.415 817.467) 
(list 1205.415 817.29) 
(list 1279.4375 817.84)))
(apply 'command (append '("pline") coords '("c")))
(setq currobj (ssadd (entlast) currobj))
(setq coords (list 
(list 1279.4375 817.697) 
(list 1205.415 817.147) 
(list 1205.415 816.97) 
(list 1279.4375 817.62)))
(apply 'command (append '("pline") coords '("c")))
(setq currobj (ssadd (entlast) currobj))
(setq coords (list 
(list 1279.4375 817.477) 
(list 1205.415 816.827) 
(list 1205.415 816.65) 
(list 1279.4375 817.4)))
(apply 'command (append '("pline") coords '("c")))
(setq currobj (ssadd (entlast) currobj))
(command "_layer" "set" "nitride" "")
(command "_layer" "set" "text" "")
(command "_circle" "1279.0625,806.257" "0.075")
(command "_circle" "1279.0625,806.557" "0.075")
(command "_circle" "1279.0625,806.857" "0.075")
(command "_circle" "1279.0625,807.157" "0.075")
(command "_circle" "1279.0625,807.457" "0.075")
(command "_circle" "1278.7625,806.257" "0.075")
(command "_circle" "1278.7625,806.557" "0.075")
(command "_circle" "1278.7625,806.857" "0.075")
(command "_circle" "1278.7625,807.157" "0.075")
(command "_circle" "1278.7625,807.457" "0.075")
(command "_circle" "1278.4625,806.257" "0.075")
(command "_circle" "1278.4625,806.557" "0.075")
(command "_circle" "1278.4625,806.857" "0.075")
(command "_circle" "1278.4625,807.157" "0.075")
(command "_circle" "1278.4625,807.457" "0.075")
(command "_circle" "1278.1625,806.257" "0.075")
(command "_circle" "1278.1625,806.557" "0.075")
(command "_circle" "1278.1625,806.857" "0.075")
(command "_circle" "1278.1625,807.157" "0.075")
(command "_circle" "1278.1625,807.457" "0.075")
(command "_circle" "1277.8625,806.257" "0.075")
(command "_circle" "1277.8625,806.557" "0.075")
(command "_circle" "1277.8625,806.857" "0.075")
(command "_circle" "1277.8625,807.157" "0.075")
(command "_circle" "1277.8625,807.457" "0.075")
(command "_layer" "set" "nitride" "")
(setq coords (list 
(list 1280.2625 831.7) 
(list 1280.2625 836.7) 
(list 1279.7375 836.7) 
(list 1279.7375 831.7)))
(apply 'command (append '("pline") coords '("c")))
(setq currobj (ssadd (entlast) currobj))
(command "_layer" "set" "prebias" "")
(command "_rectangle" "1279.7375,831.7" "1280.2625,836.7")
(setq currobj (ssadd (entlast) currobj))
(command "_layer" "set" "nitride" "")
(setq cooledsinglenanobeam4 currobj)
(setq currobj nil)
(setq currobj (ssadd))
; DRAWING PHOTONIC CRYSTAL
(command "_layer" "set" "negYjunc" "")
(setq coords (list 
(list 1280.125 866.7) 
(list 1280 851.7) 
(list 1280 866.7)))
(apply 'command (append '("pline") coords '("c")))
(setq currobj (ssadd (entlast) currobj))
(setq coords (list 
(list 1280.2625 836.7) 
(list 1280.405 866.7) 
(list 1281.112 866.7) 
(list 1281.112 836.7)))
(apply 'command (append '("pline") coords '("c")))
(setq currobj (ssadd (entlast) currobj))
(setq coords (list 
(list 1279.875 866.7) 
(list 1280 851.7) 
(list 1280 866.7)))
(apply 'command (append '("pline") coords '("c")))
(setq currobj (ssadd (entlast) currobj))
(setq coords (list 
(list 1279.7375 836.7) 
(list 1279.595 866.7) 
(list 1278.888 866.7) 
(list 1278.888 836.7)))
(apply 'command (append '("pline") coords '("c")))
(setq currobj (ssadd (entlast) currobj))
(command "_layer" "set" "nitride" "")
(setq yjunction4 currobj)
(setq currobj nil)
(setq currobj (ssadd))
(setq tap4 nil)
(setq tap4 (ssadd))
(command "_layer" "set" "phc" "")
(setq coords (list 
(list 1280 866.7) 
(list 1280.125 866.7) 
(list 1280.125 866.7103) 
(list 1280.125 866.7206) 
(list 1280.125 866.7308) 
(list 1280.125 866.7411) 
(list 1280.125 866.7514) 
(list 1280.125 866.7617) 
(list 1280.125 866.7719) 
(list 1280.125 866.7822) 
(list 1280.125 866.7925) 
(list 1280.125 866.8028) 
(list 1280.125 866.8131) 
(list 1280.125 866.8233) 
(list 1280.125 866.8336) 
(list 1280.125 866.8439) 
(list 1280.125 866.8542) 
(list 1280.125 866.8644) 
(list 1280.125 866.8747) 
(list 1280.125 866.885) 
(list 1280.125 866.8953) 
(list 1280.125 866.9056) 
(list 1280.125 866.9158) 
(list 1280.125 866.9261) 
(list 1280.125 866.9364) 
(list 1280.125 866.9467) 
(list 1280.125 866.9569) 
(list 1280.125 866.9672) 
(list 1280.125 866.9775) 
(list 1280.125 866.9878) 
(list 1280.125 866.9981) 
(list 1280.125 867.0083) 
(list 1280.125 867.0186) 
(list 1280.125 867.0289) 
(list 1280.125 867.0392) 
(list 1280.125 867.0494) 
(list 1280.125 867.0597) 
(list 1280.125 867.07) 
(list 1280 867.07)))
(apply 'command (append '("pline") coords '("c")))
(setq tap4 (ssadd (entlast) tap4))
(command "_mirror" (entlast) "" "1280,900" "1280,901" "No")
(setq tap4 (ssadd (entlast) tap4))
(setq coords (list 
(list 1280.4151 866.7) 
(list 1280.405 866.7) 
(list 1280.4053 866.7103) 
(list 1280.4055 866.7206) 
(list 1280.4057 866.7308) 
(list 1280.4059 866.7411) 
(list 1280.4059 866.7514) 
(list 1280.4059 866.7617) 
(list 1280.4057 866.7719) 
(list 1280.4055 866.7822) 
(list 1280.4052 866.7925) 
(list 1280.4047 866.8028) 
(list 1280.4042 866.8131) 
(list 1280.4036 866.8233) 
(list 1280.403 866.8336) 
(list 1280.4024 866.8439) 
(list 1280.4018 866.8542) 
(list 1280.4013 866.8644) 
(list 1280.4009 866.8747) 
(list 1280.4006 866.885) 
(list 1280.4004 866.8953) 
(list 1280.4004 866.9056) 
(list 1280.4006 866.9158) 
(list 1280.4009 866.9261) 
(list 1280.4015 866.9364) 
(list 1280.4022 866.9467) 
(list 1280.4032 866.9569) 
(list 1280.4042 866.9672) 
(list 1280.4054 866.9775) 
(list 1280.4067 866.9878) 
(list 1280.4081 866.9981) 
(list 1280.4094 867.0083) 
(list 1280.4108 867.0186) 
(list 1280.412 867.0289) 
(list 1280.4131 867.0392) 
(list 1280.414 867.0494) 
(list 1280.4146 867.0597) 
(list 1280.4151 867.07) 
(list 1280.4151 867.07)))
(apply 'command (append '("pline") coords '("c")))
(setq tap4 (ssadd (entlast) tap4))
(command "_mirror" (entlast) "" "1280,900" "1280,901" "No")
(setq tap4 (ssadd (entlast) tap4))
(setq coords (list 
(list 1281.112 866.7) 
(list 1280.4151 866.7) 
(list 1280.4151 866.7103) 
(list 1280.4151 866.7206) 
(list 1280.4151 866.7308) 
(list 1280.4151 866.7411) 
(list 1280.4151 866.7514) 
(list 1280.4151 866.7617) 
(list 1280.4151 866.7719) 
(list 1280.4151 866.7822) 
(list 1280.4151 866.7925) 
(list 1280.4151 866.8028) 
(list 1280.4151 866.8131) 
(list 1280.4151 866.8233) 
(list 1280.4151 866.8336) 
(list 1280.4151 866.8439) 
(list 1280.4151 866.8542) 
(list 1280.4151 866.8644) 
(list 1280.4151 866.8747) 
(list 1280.4151 866.885) 
(list 1280.4151 866.8953) 
(list 1280.4151 866.9056) 
(list 1280.4151 866.9158) 
(list 1280.4151 866.9261) 
(list 1280.4151 866.9364) 
(list 1280.4151 866.9467) 
(list 1280.4151 866.9569) 
(list 1280.4151 866.9672) 
(list 1280.4151 866.9775) 
(list 1280.4151 866.9878) 
(list 1280.4151 866.9981) 
(list 1280.4151 867.0083) 
(list 1280.4151 867.0186) 
(list 1280.4151 867.0289) 
(list 1280.4151 867.0392) 
(list 1280.4151 867.0494) 
(list 1280.4151 867.0597) 
(list 1280.4151 867.07) 
(list 1281.112 867.07)))
(apply 'command (append '("pline") coords '("c")))
(setq tap4 (ssadd (entlast) tap4))
(command "_mirror" (entlast) "" "1280,900" "1280,901" "No")
(setq tap4 (ssadd (entlast) tap4))
(setq coords (list 
(list 1280 867.07) 
(list 1280.125 867.07) 
(list 1280.125 867.0803) 
(list 1280.125 867.0906) 
(list 1280.125 867.1008) 
(list 1280.125 867.1111) 
(list 1280.125 867.1214) 
(list 1280.125 867.1317) 
(list 1280.125 867.1419) 
(list 1280.125 867.1522) 
(list 1280.125 867.1625) 
(list 1280.125 867.1728) 
(list 1280.125 867.1831) 
(list 1280.125 867.1933) 
(list 1280.125 867.2036) 
(list 1280.125 867.2139) 
(list 1280.125 867.2242) 
(list 1280.125 867.2344) 
(list 1280.125 867.2447) 
(list 1280.125 867.255) 
(list 1280.125 867.2653) 
(list 1280.125 867.2756) 
(list 1280.125 867.2858) 
(list 1280.125 867.2961) 
(list 1280.125 867.3064) 
(list 1280.125 867.3167) 
(list 1280.125 867.3269) 
(list 1280.125 867.3372) 
(list 1280.125 867.3475) 
(list 1280.125 867.3578) 
(list 1280.125 867.3681) 
(list 1280.125 867.3783) 
(list 1280.125 867.3886) 
(list 1280.125 867.3989) 
(list 1280.125 867.4092) 
(list 1280.125 867.4194) 
(list 1280.125 867.4297) 
(list 1280.125 867.44) 
(list 1280 867.44)))
(apply 'command (append '("pline") coords '("c")))
(setq tap4 (ssadd (entlast) tap4))
(command "_mirror" (entlast) "" "1280,900" "1280,901" "No")
(setq tap4 (ssadd (entlast) tap4))
(setq coords (list 
(list 1280.4251 867.07) 
(list 1280.4151 867.07) 
(list 1280.4152 867.0803) 
(list 1280.415 867.0906) 
(list 1280.4145 867.1008) 
(list 1280.4137 867.1111) 
(list 1280.4126 867.1214) 
(list 1280.4112 867.1317) 
(list 1280.4096 867.1419) 
(list 1280.4077 867.1522) 
(list 1280.4057 867.1625) 
(list 1280.4037 867.1728) 
(list 1280.4016 867.1831) 
(list 1280.3995 867.1933) 
(list 1280.3975 867.2036) 
(list 1280.3958 867.2139) 
(list 1280.3942 867.2242) 
(list 1280.393 867.2344) 
(list 1280.3922 867.2447) 
(list 1280.3917 867.255) 
(list 1280.3917 867.2653) 
(list 1280.3921 867.2756) 
(list 1280.393 867.2858) 
(list 1280.3943 867.2961) 
(list 1280.396 867.3064) 
(list 1280.3981 867.3167) 
(list 1280.4005 867.3269) 
(list 1280.4032 867.3372) 
(list 1280.4061 867.3475) 
(list 1280.409 867.3578) 
(list 1280.4119 867.3681) 
(list 1280.4148 867.3783) 
(list 1280.4174 867.3886) 
(list 1280.4198 867.3989) 
(list 1280.4219 867.4092) 
(list 1280.4235 867.4194) 
(list 1280.4246 867.4297) 
(list 1280.4251 867.44) 
(list 1280.4251 867.44)))
(apply 'command (append '("pline") coords '("c")))
(setq tap4 (ssadd (entlast) tap4))
(command "_mirror" (entlast) "" "1280,900" "1280,901" "No")
(setq tap4 (ssadd (entlast) tap4))
(setq coords (list 
(list 1281.112 867.07) 
(list 1280.4251 867.07) 
(list 1280.4251 867.0803) 
(list 1280.4251 867.0906) 
(list 1280.4251 867.1008) 
(list 1280.4251 867.1111) 
(list 1280.4251 867.1214) 
(list 1280.4251 867.1317) 
(list 1280.4251 867.1419) 
(list 1280.4251 867.1522) 
(list 1280.4251 867.1625) 
(list 1280.4251 867.1728) 
(list 1280.4251 867.1831) 
(list 1280.4251 867.1933) 
(list 1280.4251 867.2036) 
(list 1280.4251 867.2139) 
(list 1280.4251 867.2242) 
(list 1280.4251 867.2344) 
(list 1280.4251 867.2447) 
(list 1280.4251 867.255) 
(list 1280.4251 867.2653) 
(list 1280.4251 867.2756) 
(list 1280.4251 867.2858) 
(list 1280.4251 867.2961) 
(list 1280.4251 867.3064) 
(list 1280.4251 867.3167) 
(list 1280.4251 867.3269) 
(list 1280.4251 867.3372) 
(list 1280.4251 867.3475) 
(list 1280.4251 867.3578) 
(list 1280.4251 867.3681) 
(list 1280.4251 867.3783) 
(list 1280.4251 867.3886) 
(list 1280.4251 867.3989) 
(list 1280.4251 867.4092) 
(list 1280.4251 867.4194) 
(list 1280.4251 867.4297) 
(list 1280.4251 867.44) 
(list 1281.112 867.44)))
(apply 'command (append '("pline") coords '("c")))
(setq tap4 (ssadd (entlast) tap4))
(command "_mirror" (entlast) "" "1280,900" "1280,901" "No")
(setq tap4 (ssadd (entlast) tap4))
(setq coords (list 
(list 1280 867.44) 
(list 1280.125 867.44) 
(list 1280.125 867.4503) 
(list 1280.125 867.4606) 
(list 1280.125 867.4708) 
(list 1280.125 867.4811) 
(list 1280.125 867.4914) 
(list 1280.125 867.5017) 
(list 1280.125 867.5119) 
(list 1280.125 867.5222) 
(list 1280.125 867.5325) 
(list 1280.125 867.5428) 
(list 1280.125 867.5531) 
(list 1280.125 867.5633) 
(list 1280.125 867.5736) 
(list 1280.125 867.5839) 
(list 1280.125 867.5942) 
(list 1280.125 867.6044) 
(list 1280.125 867.6147) 
(list 1280.125 867.625) 
(list 1280.125 867.6353) 
(list 1280.125 867.6456) 
(list 1280.125 867.6558) 
(list 1280.125 867.6661) 
(list 1280.125 867.6764) 
(list 1280.125 867.6867) 
(list 1280.125 867.6969) 
(list 1280.125 867.7072) 
(list 1280.125 867.7175) 
(list 1280.125 867.7278) 
(list 1280.125 867.7381) 
(list 1280.125 867.7483) 
(list 1280.125 867.7586) 
(list 1280.125 867.7689) 
(list 1280.125 867.7792) 
(list 1280.125 867.7894) 
(list 1280.125 867.7997) 
(list 1280.125 867.81) 
(list 1280 867.81)))
(apply 'command (append '("pline") coords '("c")))
(setq tap4 (ssadd (entlast) tap4))
(command "_mirror" (entlast) "" "1280,900" "1280,901" "No")
(setq tap4 (ssadd (entlast) tap4))
(setq coords (list 
(list 1280.4352 867.44) 
(list 1280.4251 867.44) 
(list 1280.4251 867.4503) 
(list 1280.4245 867.4606) 
(list 1280.4233 867.4708) 
(list 1280.4216 867.4811) 
(list 1280.4193 867.4914) 
(list 1280.4166 867.5017) 
(list 1280.4134 867.5119) 
(list 1280.41 867.5222) 
(list 1280.4063 867.5325) 
(list 1280.4026 867.5428) 
(list 1280.3989 867.5531) 
(list 1280.3954 867.5633) 
(list 1280.392 867.5736) 
(list 1280.3891 867.5839) 
(list 1280.3866 867.5942) 
(list 1280.3847 867.6044) 
(list 1280.3834 867.6147) 
(list 1280.3828 867.625) 
(list 1280.3829 867.6353) 
(list 1280.3838 867.6456) 
(list 1280.3854 867.6558) 
(list 1280.3876 867.6661) 
(list 1280.3905 867.6764) 
(list 1280.394 867.6867) 
(list 1280.3979 867.6969) 
(list 1280.4022 867.7072) 
(list 1280.4066 867.7175) 
(list 1280.4112 867.7278) 
(list 1280.4158 867.7381) 
(list 1280.4201 867.7483) 
(list 1280.4241 867.7586) 
(list 1280.4277 867.7689) 
(list 1280.4307 867.7792) 
(list 1280.433 867.7894) 
(list 1280.4345 867.7997) 
(list 1280.4352 867.81) 
(list 1280.4352 867.81)))
(apply 'command (append '("pline") coords '("c")))
(setq tap4 (ssadd (entlast) tap4))
(command "_mirror" (entlast) "" "1280,900" "1280,901" "No")
(setq tap4 (ssadd (entlast) tap4))
(setq coords (list 
(list 1281.112 867.44) 
(list 1280.4352 867.44) 
(list 1280.4352 867.4503) 
(list 1280.4352 867.4606) 
(list 1280.4352 867.4708) 
(list 1280.4352 867.4811) 
(list 1280.4352 867.4914) 
(list 1280.4352 867.5017) 
(list 1280.4352 867.5119) 
(list 1280.4352 867.5222) 
(list 1280.4352 867.5325) 
(list 1280.4352 867.5428) 
(list 1280.4352 867.5531) 
(list 1280.4352 867.5633) 
(list 1280.4352 867.5736) 
(list 1280.4352 867.5839) 
(list 1280.4352 867.5942) 
(list 1280.4352 867.6044) 
(list 1280.4352 867.6147) 
(list 1280.4352 867.625) 
(list 1280.4352 867.6353) 
(list 1280.4352 867.6456) 
(list 1280.4352 867.6558) 
(list 1280.4352 867.6661) 
(list 1280.4352 867.6764) 
(list 1280.4352 867.6867) 
(list 1280.4352 867.6969) 
(list 1280.4352 867.7072) 
(list 1280.4352 867.7175) 
(list 1280.4352 867.7278) 
(list 1280.4352 867.7381) 
(list 1280.4352 867.7483) 
(list 1280.4352 867.7586) 
(list 1280.4352 867.7689) 
(list 1280.4352 867.7792) 
(list 1280.4352 867.7894) 
(list 1280.4352 867.7997) 
(list 1280.4352 867.81) 
(list 1281.112 867.81)))
(apply 'command (append '("pline") coords '("c")))
(setq tap4 (ssadd (entlast) tap4))
(command "_mirror" (entlast) "" "1280,900" "1280,901" "No")
(setq tap4 (ssadd (entlast) tap4))
(setq coords (list 
(list 1280 867.81) 
(list 1280.125 867.81) 
(list 1280.125 867.8203) 
(list 1280.125 867.8306) 
(list 1280.125 867.8408) 
(list 1280.125 867.8511) 
(list 1280.125 867.8614) 
(list 1280.125 867.8717) 
(list 1280.125 867.8819) 
(list 1280.125 867.8922) 
(list 1280.125 867.9025) 
(list 1280.125 867.9128) 
(list 1280.125 867.9231) 
(list 1280.125 867.9333) 
(list 1280.125 867.9436) 
(list 1280.125 867.9539) 
(list 1280.125 867.9642) 
(list 1280.125 867.9744) 
(list 1280.125 867.9847) 
(list 1280.125 867.995) 
(list 1280.125 868.0053) 
(list 1280.125 868.0156) 
(list 1280.125 868.0258) 
(list 1280.125 868.0361) 
(list 1280.125 868.0464) 
(list 1280.125 868.0567) 
(list 1280.125 868.0669) 
(list 1280.125 868.0772) 
(list 1280.125 868.0875) 
(list 1280.125 868.0978) 
(list 1280.125 868.1081) 
(list 1280.125 868.1183) 
(list 1280.125 868.1286) 
(list 1280.125 868.1389) 
(list 1280.125 868.1492) 
(list 1280.125 868.1594) 
(list 1280.125 868.1697) 
(list 1280.125 868.18) 
(list 1280 868.18)))
(apply 'command (append '("pline") coords '("c")))
(setq tap4 (ssadd (entlast) tap4))
(command "_mirror" (entlast) "" "1280,900" "1280,901" "No")
(setq tap4 (ssadd (entlast) tap4))
(setq coords (list 
(list 1280.4453 867.81) 
(list 1280.4352 867.81) 
(list 1280.435 867.8203) 
(list 1280.434 867.8306) 
(list 1280.4321 867.8408) 
(list 1280.4294 867.8511) 
(list 1280.426 867.8614) 
(list 1280.4219 867.8717) 
(list 1280.4173 867.8819) 
(list 1280.4122 867.8922) 
(list 1280.407 867.9025) 
(list 1280.4016 867.9128) 
(list 1280.3963 867.9231) 
(list 1280.3912 867.9333) 
(list 1280.3866 867.9436) 
(list 1280.3825 867.9539) 
(list 1280.379 867.9642) 
(list 1280.3764 867.9744) 
(list 1280.3747 867.9847) 
(list 1280.374 867.995) 
(list 1280.3742 868.0053) 
(list 1280.3755 868.0156) 
(list 1280.3778 868.0258) 
(list 1280.381 868.0361) 
(list 1280.385 868.0464) 
(list 1280.3898 868.0567) 
(list 1280.3953 868.0669) 
(list 1280.4011 868.0772) 
(list 1280.4072 868.0875) 
(list 1280.4135 868.0978) 
(list 1280.4196 868.1081) 
(list 1280.4254 868.1183) 
(list 1280.4308 868.1286) 
(list 1280.4355 868.1389) 
(list 1280.4395 868.1492) 
(list 1280.4425 868.1594) 
(list 1280.4444 868.1697) 
(list 1280.4453 868.18) 
(list 1280.4453 868.18)))
(apply 'command (append '("pline") coords '("c")))
(setq tap4 (ssadd (entlast) tap4))
(command "_mirror" (entlast) "" "1280,900" "1280,901" "No")
(setq tap4 (ssadd (entlast) tap4))
(setq coords (list 
(list 1281.112 867.81) 
(list 1280.4453 867.81) 
(list 1280.4453 867.8203) 
(list 1280.4453 867.8306) 
(list 1280.4453 867.8408) 
(list 1280.4453 867.8511) 
(list 1280.4453 867.8614) 
(list 1280.4453 867.8717) 
(list 1280.4453 867.8819) 
(list 1280.4453 867.8922) 
(list 1280.4453 867.9025) 
(list 1280.4453 867.9128) 
(list 1280.4453 867.9231) 
(list 1280.4453 867.9333) 
(list 1280.4453 867.9436) 
(list 1280.4453 867.9539) 
(list 1280.4453 867.9642) 
(list 1280.4453 867.9744) 
(list 1280.4453 867.9847) 
(list 1280.4453 867.995) 
(list 1280.4453 868.0053) 
(list 1280.4453 868.0156) 
(list 1280.4453 868.0258) 
(list 1280.4453 868.0361) 
(list 1280.4453 868.0464) 
(list 1280.4453 868.0567) 
(list 1280.4453 868.0669) 
(list 1280.4453 868.0772) 
(list 1280.4453 868.0875) 
(list 1280.4453 868.0978) 
(list 1280.4453 868.1081) 
(list 1280.4453 868.1183) 
(list 1280.4453 868.1286) 
(list 1280.4453 868.1389) 
(list 1280.4453 868.1492) 
(list 1280.4453 868.1594) 
(list 1280.4453 868.1697) 
(list 1280.4453 868.18) 
(list 1281.112 868.18)))
(apply 'command (append '("pline") coords '("c")))
(setq tap4 (ssadd (entlast) tap4))
(command "_mirror" (entlast) "" "1280,900" "1280,901" "No")
(setq tap4 (ssadd (entlast) tap4))
(setq coords (list 
(list 1280 868.18) 
(list 1280.125 868.18) 
(list 1280.125 868.1903) 
(list 1280.125 868.2006) 
(list 1280.125 868.2108) 
(list 1280.125 868.2211) 
(list 1280.125 868.2314) 
(list 1280.125 868.2417) 
(list 1280.125 868.2519) 
(list 1280.125 868.2622) 
(list 1280.125 868.2725) 
(list 1280.125 868.2828) 
(list 1280.125 868.2931) 
(list 1280.125 868.3033) 
(list 1280.125 868.3136) 
(list 1280.125 868.3239) 
(list 1280.125 868.3342) 
(list 1280.125 868.3444) 
(list 1280.125 868.3547) 
(list 1280.125 868.365) 
(list 1280.125 868.3753) 
(list 1280.125 868.3856) 
(list 1280.125 868.3958) 
(list 1280.125 868.4061) 
(list 1280.125 868.4164) 
(list 1280.125 868.4267) 
(list 1280.125 868.4369) 
(list 1280.125 868.4472) 
(list 1280.125 868.4575) 
(list 1280.125 868.4678) 
(list 1280.125 868.4781) 
(list 1280.125 868.4883) 
(list 1280.125 868.4986) 
(list 1280.125 868.5089) 
(list 1280.125 868.5192) 
(list 1280.125 868.5294) 
(list 1280.125 868.5397) 
(list 1280.125 868.55) 
(list 1280 868.55)))
(apply 'command (append '("pline") coords '("c")))
(setq tap4 (ssadd (entlast) tap4))
(command "_mirror" (entlast) "" "1280,900" "1280,901" "No")
(setq tap4 (ssadd (entlast) tap4))
(setq coords (list 
(list 1280.4553 868.18) 
(list 1280.4453 868.18) 
(list 1280.445 868.1903) 
(list 1280.4435 868.2006) 
(list 1280.4409 868.2108) 
(list 1280.4373 868.2211) 
(list 1280.4327 868.2314) 
(list 1280.4272 868.2417) 
(list 1280.4211 868.2519) 
(list 1280.4145 868.2622) 
(list 1280.4075 868.2725) 
(list 1280.4005 868.2828) 
(list 1280.3936 868.2931) 
(list 1280.3871 868.3033) 
(list 1280.3811 868.3136) 
(list 1280.3758 868.3239) 
(list 1280.3714 868.3342) 
(list 1280.3681 868.3444) 
(list 1280.366 868.3547) 
(list 1280.3651 868.365) 
(list 1280.3655 868.3753) 
(list 1280.3672 868.3856) 
(list 1280.3702 868.3958) 
(list 1280.3743 868.4061) 
(list 1280.3796 868.4164) 
(list 1280.3857 868.4267) 
(list 1280.3926 868.4369) 
(list 1280.4001 868.4472) 
(list 1280.4079 868.4575) 
(list 1280.4157 868.4678) 
(list 1280.4234 868.4781) 
(list 1280.4308 868.4883) 
(list 1280.4375 868.4986) 
(list 1280.4434 868.5089) 
(list 1280.4483 868.5192) 
(list 1280.452 868.5294) 
(list 1280.4543 868.5397) 
(list 1280.4553 868.55) 
(list 1280.4553 868.55)))
(apply 'command (append '("pline") coords '("c")))
(setq tap4 (ssadd (entlast) tap4))
(command "_mirror" (entlast) "" "1280,900" "1280,901" "No")
(setq tap4 (ssadd (entlast) tap4))
(setq coords (list 
(list 1281.112 868.18) 
(list 1280.4553 868.18) 
(list 1280.4553 868.1903) 
(list 1280.4553 868.2006) 
(list 1280.4553 868.2108) 
(list 1280.4553 868.2211) 
(list 1280.4553 868.2314) 
(list 1280.4553 868.2417) 
(list 1280.4553 868.2519) 
(list 1280.4553 868.2622) 
(list 1280.4553 868.2725) 
(list 1280.4553 868.2828) 
(list 1280.4553 868.2931) 
(list 1280.4553 868.3033) 
(list 1280.4553 868.3136) 
(list 1280.4553 868.3239) 
(list 1280.4553 868.3342) 
(list 1280.4553 868.3444) 
(list 1280.4553 868.3547) 
(list 1280.4553 868.365) 
(list 1280.4553 868.3753) 
(list 1280.4553 868.3856) 
(list 1280.4553 868.3958) 
(list 1280.4553 868.4061) 
(list 1280.4553 868.4164) 
(list 1280.4553 868.4267) 
(list 1280.4553 868.4369) 
(list 1280.4553 868.4472) 
(list 1280.4553 868.4575) 
(list 1280.4553 868.4678) 
(list 1280.4553 868.4781) 
(list 1280.4553 868.4883) 
(list 1280.4553 868.4986) 
(list 1280.4553 868.5089) 
(list 1280.4553 868.5192) 
(list 1280.4553 868.5294) 
(list 1280.4553 868.5397) 
(list 1280.4553 868.55) 
(list 1281.112 868.55)))
(apply 'command (append '("pline") coords '("c")))
(setq tap4 (ssadd (entlast) tap4))
(command "_mirror" (entlast) "" "1280,900" "1280,901" "No")
(setq tap4 (ssadd (entlast) tap4))
(setq coords (list 
(list 1280 868.55) 
(list 1280.125 868.55) 
(list 1280.125 868.5603) 
(list 1280.125 868.5706) 
(list 1280.125 868.5808) 
(list 1280.125 868.5911) 
(list 1280.125 868.6014) 
(list 1280.125 868.6117) 
(list 1280.125 868.6219) 
(list 1280.125 868.6322) 
(list 1280.125 868.6425) 
(list 1280.125 868.6528) 
(list 1280.125 868.6631) 
(list 1280.125 868.6733) 
(list 1280.125 868.6836) 
(list 1280.125 868.6939) 
(list 1280.125 868.7042) 
(list 1280.125 868.7144) 
(list 1280.125 868.7247) 
(list 1280.125 868.735) 
(list 1280.125 868.7453) 
(list 1280.125 868.7556) 
(list 1280.125 868.7658) 
(list 1280.125 868.7761) 
(list 1280.125 868.7864) 
(list 1280.125 868.7967) 
(list 1280.125 868.8069) 
(list 1280.125 868.8172) 
(list 1280.125 868.8275) 
(list 1280.125 868.8378) 
(list 1280.125 868.8481) 
(list 1280.125 868.8583) 
(list 1280.125 868.8686) 
(list 1280.125 868.8789) 
(list 1280.125 868.8892) 
(list 1280.125 868.8994) 
(list 1280.125 868.9097) 
(list 1280.125 868.92) 
(list 1280 868.92)))
(apply 'command (append '("pline") coords '("c")))
(setq tap4 (ssadd (entlast) tap4))
(command "_mirror" (entlast) "" "1280,900" "1280,901" "No")
(setq tap4 (ssadd (entlast) tap4))
(setq coords (list 
(list 1280.4654 868.55) 
(list 1280.4553 868.55) 
(list 1280.4549 868.5603) 
(list 1280.453 868.5706) 
(list 1280.4497 868.5808) 
(list 1280.4451 868.5911) 
(list 1280.4394 868.6014) 
(list 1280.4326 868.6117) 
(list 1280.4249 868.6219) 
(list 1280.4167 868.6322) 
(list 1280.4081 868.6425) 
(list 1280.3995 868.6528) 
(list 1280.391 868.6631) 
(list 1280.383 868.6733) 
(list 1280.3756 868.6836) 
(list 1280.3692 868.6939) 
(list 1280.3638 868.7042) 
(list 1280.3598 868.7144) 
(list 1280.3573 868.7247) 
(list 1280.3562 868.735) 
(list 1280.3568 868.7453) 
(list 1280.3589 868.7556) 
(list 1280.3626 868.7658) 
(list 1280.3677 868.7761) 
(list 1280.3741 868.7864) 
(list 1280.3816 868.7967) 
(list 1280.39 868.8069) 
(list 1280.399 868.8172) 
(list 1280.4084 868.8275) 
(list 1280.418 868.8378) 
(list 1280.4273 868.8481) 
(list 1280.4361 868.8583) 
(list 1280.4442 868.8686) 
(list 1280.4512 868.8789) 
(list 1280.4571 868.8892) 
(list 1280.4614 868.8994) 
(list 1280.4643 868.9097) 
(list 1280.4654 868.92) 
(list 1280.4654 868.92)))
(apply 'command (append '("pline") coords '("c")))
(setq tap4 (ssadd (entlast) tap4))
(command "_mirror" (entlast) "" "1280,900" "1280,901" "No")
(setq tap4 (ssadd (entlast) tap4))
(setq coords (list 
(list 1281.112 868.55) 
(list 1280.4654 868.55) 
(list 1280.4654 868.5603) 
(list 1280.4654 868.5706) 
(list 1280.4654 868.5808) 
(list 1280.4654 868.5911) 
(list 1280.4654 868.6014) 
(list 1280.4654 868.6117) 
(list 1280.4654 868.6219) 
(list 1280.4654 868.6322) 
(list 1280.4654 868.6425) 
(list 1280.4654 868.6528) 
(list 1280.4654 868.6631) 
(list 1280.4654 868.6733) 
(list 1280.4654 868.6836) 
(list 1280.4654 868.6939) 
(list 1280.4654 868.7042) 
(list 1280.4654 868.7144) 
(list 1280.4654 868.7247) 
(list 1280.4654 868.735) 
(list 1280.4654 868.7453) 
(list 1280.4654 868.7556) 
(list 1280.4654 868.7658) 
(list 1280.4654 868.7761) 
(list 1280.4654 868.7864) 
(list 1280.4654 868.7967) 
(list 1280.4654 868.8069) 
(list 1280.4654 868.8172) 
(list 1280.4654 868.8275) 
(list 1280.4654 868.8378) 
(list 1280.4654 868.8481) 
(list 1280.4654 868.8583) 
(list 1280.4654 868.8686) 
(list 1280.4654 868.8789) 
(list 1280.4654 868.8892) 
(list 1280.4654 868.8994) 
(list 1280.4654 868.9097) 
(list 1280.4654 868.92) 
(list 1281.112 868.92)))
(apply 'command (append '("pline") coords '("c")))
(setq tap4 (ssadd (entlast) tap4))
(command "_mirror" (entlast) "" "1280,900" "1280,901" "No")
(setq tap4 (ssadd (entlast) tap4))
(setq coords (list 
(list 1280 868.92) 
(list 1280.125 868.92) 
(list 1280.125 868.9303) 
(list 1280.125 868.9406) 
(list 1280.125 868.9508) 
(list 1280.125 868.9611) 
(list 1280.125 868.9714) 
(list 1280.125 868.9817) 
(list 1280.125 868.9919) 
(list 1280.125 869.0022) 
(list 1280.125 869.0125) 
(list 1280.125 869.0228) 
(list 1280.125 869.0331) 
(list 1280.125 869.0433) 
(list 1280.125 869.0536) 
(list 1280.125 869.0639) 
(list 1280.125 869.0742) 
(list 1280.125 869.0844) 
(list 1280.125 869.0947) 
(list 1280.125 869.105) 
(list 1280.125 869.1153) 
(list 1280.125 869.1256) 
(list 1280.125 869.1358) 
(list 1280.125 869.1461) 
(list 1280.125 869.1564) 
(list 1280.125 869.1667) 
(list 1280.125 869.1769) 
(list 1280.125 869.1872) 
(list 1280.125 869.1975) 
(list 1280.125 869.2078) 
(list 1280.125 869.2181) 
(list 1280.125 869.2283) 
(list 1280.125 869.2386) 
(list 1280.125 869.2489) 
(list 1280.125 869.2592) 
(list 1280.125 869.2694) 
(list 1280.125 869.2797) 
(list 1280.125 869.29) 
(list 1280 869.29)))
(apply 'command (append '("pline") coords '("c")))
(setq tap4 (ssadd (entlast) tap4))
(command "_mirror" (entlast) "" "1280,900" "1280,901" "No")
(setq tap4 (ssadd (entlast) tap4))
(setq coords (list 
(list 1280.4755 868.92) 
(list 1280.4654 868.92) 
(list 1280.4648 868.9303) 
(list 1280.4625 868.9406) 
(list 1280.4585 868.9508) 
(list 1280.453 868.9611) 
(list 1280.446 868.9714) 
(list 1280.4379 868.9817) 
(list 1280.4288 868.9919) 
(list 1280.419 869.0022) 
(list 1280.4088 869.0125) 
(list 1280.3984 869.0228) 
(list 1280.3884 869.0331) 
(list 1280.3788 869.0433) 
(list 1280.3701 869.0536) 
(list 1280.3625 869.0639) 
(list 1280.3562 869.0742) 
(list 1280.3515 869.0844) 
(list 1280.3485 869.0947) 
(list 1280.3474 869.105) 
(list 1280.3481 869.1153) 
(list 1280.3506 869.1256) 
(list 1280.355 869.1358) 
(list 1280.361 869.1461) 
(list 1280.3686 869.1564) 
(list 1280.3774 869.1667) 
(list 1280.3873 869.1769) 
(list 1280.398 869.1872) 
(list 1280.409 869.1975) 
(list 1280.4202 869.2078) 
(list 1280.4311 869.2181) 
(list 1280.4414 869.2283) 
(list 1280.4509 869.2386) 
(list 1280.4591 869.2489) 
(list 1280.4659 869.2592) 
(list 1280.4709 869.2694) 
(list 1280.4742 869.2797) 
(list 1280.4755 869.29) 
(list 1280.4755 869.29)))
(apply 'command (append '("pline") coords '("c")))
(setq tap4 (ssadd (entlast) tap4))
(command "_mirror" (entlast) "" "1280,900" "1280,901" "No")
(setq tap4 (ssadd (entlast) tap4))
(setq coords (list 
(list 1281.112 868.92) 
(list 1280.4755 868.92) 
(list 1280.4755 868.9303) 
(list 1280.4755 868.9406) 
(list 1280.4755 868.9508) 
(list 1280.4755 868.9611) 
(list 1280.4755 868.9714) 
(list 1280.4755 868.9817) 
(list 1280.4755 868.9919) 
(list 1280.4755 869.0022) 
(list 1280.4755 869.0125) 
(list 1280.4755 869.0228) 
(list 1280.4755 869.0331) 
(list 1280.4755 869.0433) 
(list 1280.4755 869.0536) 
(list 1280.4755 869.0639) 
(list 1280.4755 869.0742) 
(list 1280.4755 869.0844) 
(list 1280.4755 869.0947) 
(list 1280.4755 869.105) 
(list 1280.4755 869.1153) 
(list 1280.4755 869.1256) 
(list 1280.4755 869.1358) 
(list 1280.4755 869.1461) 
(list 1280.4755 869.1564) 
(list 1280.4755 869.1667) 
(list 1280.4755 869.1769) 
(list 1280.4755 869.1872) 
(list 1280.4755 869.1975) 
(list 1280.4755 869.2078) 
(list 1280.4755 869.2181) 
(list 1280.4755 869.2283) 
(list 1280.4755 869.2386) 
(list 1280.4755 869.2489) 
(list 1280.4755 869.2592) 
(list 1280.4755 869.2694) 
(list 1280.4755 869.2797) 
(list 1280.4755 869.29) 
(list 1281.112 869.29)))
(apply 'command (append '("pline") coords '("c")))
(setq tap4 (ssadd (entlast) tap4))
(command "_mirror" (entlast) "" "1280,900" "1280,901" "No")
(setq tap4 (ssadd (entlast) tap4))
(setq coords (list 
(list 1280 869.29) 
(list 1280.125 869.29) 
(list 1280.125 869.3003) 
(list 1280.125 869.3106) 
(list 1280.125 869.3208) 
(list 1280.125 869.3311) 
(list 1280.125 869.3414) 
(list 1280.125 869.3517) 
(list 1280.125 869.3619) 
(list 1280.125 869.3722) 
(list 1280.125 869.3825) 
(list 1280.125 869.3928) 
(list 1280.125 869.4031) 
(list 1280.125 869.4133) 
(list 1280.125 869.4236) 
(list 1280.125 869.4339) 
(list 1280.125 869.4442) 
(list 1280.125 869.4544) 
(list 1280.125 869.4647) 
(list 1280.125 869.475) 
(list 1280.125 869.4853) 
(list 1280.125 869.4956) 
(list 1280.125 869.5058) 
(list 1280.125 869.5161) 
(list 1280.125 869.5264) 
(list 1280.125 869.5367) 
(list 1280.125 869.5469) 
(list 1280.125 869.5572) 
(list 1280.125 869.5675) 
(list 1280.125 869.5778) 
(list 1280.125 869.5881) 
(list 1280.125 869.5983) 
(list 1280.125 869.6086) 
(list 1280.125 869.6189) 
(list 1280.125 869.6292) 
(list 1280.125 869.6394) 
(list 1280.125 869.6497) 
(list 1280.125 869.66) 
(list 1280 869.66)))
(apply 'command (append '("pline") coords '("c")))
(setq tap4 (ssadd (entlast) tap4))
(command "_mirror" (entlast) "" "1280,900" "1280,901" "No")
(setq tap4 (ssadd (entlast) tap4))
(setq coords (list 
(list 1280.4855 869.29) 
(list 1280.4755 869.29) 
(list 1280.4747 869.3003) 
(list 1280.472 869.3106) 
(list 1280.4673 869.3208) 
(list 1280.4608 869.3311) 
(list 1280.4527 869.3414) 
(list 1280.4432 869.3517) 
(list 1280.4326 869.3619) 
(list 1280.4212 869.3722) 
(list 1280.4093 869.3825) 
(list 1280.3974 869.3928) 
(list 1280.3857 869.4031) 
(list 1280.3747 869.4133) 
(list 1280.3646 869.4236) 
(list 1280.3558 869.4339) 
(list 1280.3486 869.4442) 
(list 1280.3432 869.4544) 
(list 1280.3398 869.4647) 
(list 1280.3385 869.475) 
(list 1280.3393 869.4853) 
(list 1280.3423 869.4956) 
(list 1280.3474 869.5058) 
(list 1280.3544 869.5161) 
(list 1280.3631 869.5264) 
(list 1280.3733 869.5367) 
(list 1280.3847 869.5469) 
(list 1280.3969 869.5572) 
(list 1280.4097 869.5675) 
(list 1280.4225 869.5778) 
(list 1280.435 869.5881) 
(list 1280.4468 869.5983) 
(list 1280.4576 869.6086) 
(list 1280.4669 869.6189) 
(list 1280.4747 869.6292) 
(list 1280.4804 869.6394) 
(list 1280.4841 869.6497) 
(list 1280.4855 869.66) 
(list 1280.4855 869.66)))
(apply 'command (append '("pline") coords '("c")))
(setq tap4 (ssadd (entlast) tap4))
(command "_mirror" (entlast) "" "1280,900" "1280,901" "No")
(setq tap4 (ssadd (entlast) tap4))
(setq coords (list 
(list 1281.112 869.29) 
(list 1280.4855 869.29) 
(list 1280.4855 869.3003) 
(list 1280.4855 869.3106) 
(list 1280.4855 869.3208) 
(list 1280.4855 869.3311) 
(list 1280.4855 869.3414) 
(list 1280.4855 869.3517) 
(list 1280.4855 869.3619) 
(list 1280.4855 869.3722) 
(list 1280.4855 869.3825) 
(list 1280.4855 869.3928) 
(list 1280.4855 869.4031) 
(list 1280.4855 869.4133) 
(list 1280.4855 869.4236) 
(list 1280.4855 869.4339) 
(list 1280.4855 869.4442) 
(list 1280.4855 869.4544) 
(list 1280.4855 869.4647) 
(list 1280.4855 869.475) 
(list 1280.4855 869.4853) 
(list 1280.4855 869.4956) 
(list 1280.4855 869.5058) 
(list 1280.4855 869.5161) 
(list 1280.4855 869.5264) 
(list 1280.4855 869.5367) 
(list 1280.4855 869.5469) 
(list 1280.4855 869.5572) 
(list 1280.4855 869.5675) 
(list 1280.4855 869.5778) 
(list 1280.4855 869.5881) 
(list 1280.4855 869.5983) 
(list 1280.4855 869.6086) 
(list 1280.4855 869.6189) 
(list 1280.4855 869.6292) 
(list 1280.4855 869.6394) 
(list 1280.4855 869.6497) 
(list 1280.4855 869.66) 
(list 1281.112 869.66)))
(apply 'command (append '("pline") coords '("c")))
(setq tap4 (ssadd (entlast) tap4))
(command "_mirror" (entlast) "" "1280,900" "1280,901" "No")
(setq tap4 (ssadd (entlast) tap4))
(setq coords (list 
(list 1280 869.66) 
(list 1280.125 869.66) 
(list 1280.125 869.6703) 
(list 1280.125 869.6806) 
(list 1280.125 869.6908) 
(list 1280.125 869.7011) 
(list 1280.125 869.7114) 
(list 1280.125 869.7217) 
(list 1280.125 869.7319) 
(list 1280.125 869.7422) 
(list 1280.125 869.7525) 
(list 1280.125 869.7628) 
(list 1280.125 869.7731) 
(list 1280.125 869.7833) 
(list 1280.125 869.7936) 
(list 1280.125 869.8039) 
(list 1280.125 869.8142) 
(list 1280.125 869.8244) 
(list 1280.125 869.8347) 
(list 1280.125 869.845) 
(list 1280.125 869.8553) 
(list 1280.125 869.8656) 
(list 1280.125 869.8758) 
(list 1280.125 869.8861) 
(list 1280.125 869.8964) 
(list 1280.125 869.9067) 
(list 1280.125 869.9169) 
(list 1280.125 869.9272) 
(list 1280.125 869.9375) 
(list 1280.125 869.9478) 
(list 1280.125 869.9581) 
(list 1280.125 869.9683) 
(list 1280.125 869.9786) 
(list 1280.125 869.9889) 
(list 1280.125 869.9992) 
(list 1280.125 870.0094) 
(list 1280.125 870.0197) 
(list 1280.125 870.03) 
(list 1280 870.03)))
(apply 'command (append '("pline") coords '("c")))
(setq tap4 (ssadd (entlast) tap4))
(command "_mirror" (entlast) "" "1280,900" "1280,901" "No")
(setq tap4 (ssadd (entlast) tap4))
(setq coords (list 
(list 1280.4956 869.66) 
(list 1280.4855 869.66) 
(list 1280.4847 869.6703) 
(list 1280.4815 869.6806) 
(list 1280.4761 869.6908) 
(list 1280.4687 869.7011) 
(list 1280.4594 869.7114) 
(list 1280.4486 869.7217) 
(list 1280.4364 869.7319) 
(list 1280.4235 869.7422) 
(list 1280.4099 869.7525) 
(list 1280.3964 869.7628) 
(list 1280.3831 869.7731) 
(list 1280.3706 869.7833) 
(list 1280.3591 869.7936) 
(list 1280.3492 869.8039) 
(list 1280.341 869.8142) 
(list 1280.3349 869.8244) 
(list 1280.3311 869.8347) 
(list 1280.3296 869.845) 
(list 1280.3306 869.8553) 
(list 1280.334 869.8656) 
(list 1280.3398 869.8758) 
(list 1280.3477 869.8861) 
(list 1280.3576 869.8964) 
(list 1280.3692 869.9067) 
(list 1280.3821 869.9169) 
(list 1280.3959 869.9272) 
(list 1280.4102 869.9375) 
(list 1280.4247 869.9478) 
(list 1280.4388 869.9581) 
(list 1280.4521 869.9683) 
(list 1280.4642 869.9786) 
(list 1280.4748 869.9889) 
(list 1280.4835 869.9992) 
(list 1280.4899 870.0094) 
(list 1280.494 870.0197) 
(list 1280.4956 870.03) 
(list 1280.4956 870.03)))
(apply 'command (append '("pline") coords '("c")))
(setq tap4 (ssadd (entlast) tap4))
(command "_mirror" (entlast) "" "1280,900" "1280,901" "No")
(setq tap4 (ssadd (entlast) tap4))
(setq coords (list 
(list 1281.112 869.66) 
(list 1280.4956 869.66) 
(list 1280.4956 869.6703) 
(list 1280.4956 869.6806) 
(list 1280.4956 869.6908) 
(list 1280.4956 869.7011) 
(list 1280.4956 869.7114) 
(list 1280.4956 869.7217) 
(list 1280.4956 869.7319) 
(list 1280.4956 869.7422) 
(list 1280.4956 869.7525) 
(list 1280.4956 869.7628) 
(list 1280.4956 869.7731) 
(list 1280.4956 869.7833) 
(list 1280.4956 869.7936) 
(list 1280.4956 869.8039) 
(list 1280.4956 869.8142) 
(list 1280.4956 869.8244) 
(list 1280.4956 869.8347) 
(list 1280.4956 869.845) 
(list 1280.4956 869.8553) 
(list 1280.4956 869.8656) 
(list 1280.4956 869.8758) 
(list 1280.4956 869.8861) 
(list 1280.4956 869.8964) 
(list 1280.4956 869.9067) 
(list 1280.4956 869.9169) 
(list 1280.4956 869.9272) 
(list 1280.4956 869.9375) 
(list 1280.4956 869.9478) 
(list 1280.4956 869.9581) 
(list 1280.4956 869.9683) 
(list 1280.4956 869.9786) 
(list 1280.4956 869.9889) 
(list 1280.4956 869.9992) 
(list 1280.4956 870.0094) 
(list 1280.4956 870.0197) 
(list 1280.4956 870.03) 
(list 1281.112 870.03)))
(apply 'command (append '("pline") coords '("c")))
(setq tap4 (ssadd (entlast) tap4))
(command "_mirror" (entlast) "" "1280,900" "1280,901" "No")
(setq tap4 (ssadd (entlast) tap4))
(setq coords (list 
(list 1280 870.03) 
(list 1280.125 870.03) 
(list 1280.125 870.0403) 
(list 1280.125 870.0506) 
(list 1280.125 870.0608) 
(list 1280.125 870.0711) 
(list 1280.125 870.0814) 
(list 1280.125 870.0917) 
(list 1280.125 870.1019) 
(list 1280.125 870.1122) 
(list 1280.125 870.1225) 
(list 1280.125 870.1328) 
(list 1280.125 870.1431) 
(list 1280.125 870.1533) 
(list 1280.125 870.1636) 
(list 1280.125 870.1739) 
(list 1280.125 870.1842) 
(list 1280.125 870.1944) 
(list 1280.125 870.2047) 
(list 1280.125 870.215) 
(list 1280.125 870.2253) 
(list 1280.125 870.2356) 
(list 1280.125 870.2458) 
(list 1280.125 870.2561) 
(list 1280.125 870.2664) 
(list 1280.125 870.2767) 
(list 1280.125 870.2869) 
(list 1280.125 870.2972) 
(list 1280.125 870.3075) 
(list 1280.125 870.3178) 
(list 1280.125 870.3281) 
(list 1280.125 870.3383) 
(list 1280.125 870.3486) 
(list 1280.125 870.3589) 
(list 1280.125 870.3692) 
(list 1280.125 870.3794) 
(list 1280.125 870.3897) 
(list 1280.125 870.4) 
(list 1280 870.4)))
(apply 'command (append '("pline") coords '("c")))
(setq tap4 (ssadd (entlast) tap4))
(command "_mirror" (entlast) "" "1280,900" "1280,901" "No")
(setq tap4 (ssadd (entlast) tap4))
(setq coords (list 
(list 1280.5057 870.03) 
(list 1280.4956 870.03) 
(list 1280.4946 870.0403) 
(list 1280.491 870.0506) 
(list 1280.4849 870.0608) 
(list 1280.4765 870.0711) 
(list 1280.4661 870.0814) 
(list 1280.4539 870.0917) 
(list 1280.4403 870.1019) 
(list 1280.4257 870.1122) 
(list 1280.4106 870.1225) 
(list 1280.3953 870.1328) 
(list 1280.3805 870.1431) 
(list 1280.3664 870.1533) 
(list 1280.3537 870.1636) 
(list 1280.3425 870.1739) 
(list 1280.3334 870.1842) 
(list 1280.3267 870.1944) 
(list 1280.3224 870.2047) 
(list 1280.3208 870.215) 
(list 1280.3219 870.2253) 
(list 1280.3257 870.2356) 
(list 1280.3322 870.2458) 
(list 1280.3411 870.2561) 
(list 1280.3521 870.2664) 
(list 1280.365 870.2767) 
(list 1280.3794 870.2869) 
(list 1280.3949 870.2972) 
(list 1280.4108 870.3075) 
(list 1280.4269 870.3178) 
(list 1280.4426 870.3281) 
(list 1280.4574 870.3383) 
(list 1280.4709 870.3486) 
(list 1280.4826 870.3589) 
(list 1280.4923 870.3692) 
(list 1280.4994 870.3794) 
(list 1280.504 870.3897) 
(list 1280.5057 870.4) 
(list 1280.5057 870.4)))
(apply 'command (append '("pline") coords '("c")))
(setq tap4 (ssadd (entlast) tap4))
(command "_mirror" (entlast) "" "1280,900" "1280,901" "No")
(setq tap4 (ssadd (entlast) tap4))
(setq coords (list 
(list 1281.112 870.03) 
(list 1280.5057 870.03) 
(list 1280.5057 870.0403) 
(list 1280.5057 870.0506) 
(list 1280.5057 870.0608) 
(list 1280.5057 870.0711) 
(list 1280.5057 870.0814) 
(list 1280.5057 870.0917) 
(list 1280.5057 870.1019) 
(list 1280.5057 870.1122) 
(list 1280.5057 870.1225) 
(list 1280.5057 870.1328) 
(list 1280.5057 870.1431) 
(list 1280.5057 870.1533) 
(list 1280.5057 870.1636) 
(list 1280.5057 870.1739) 
(list 1280.5057 870.1842) 
(list 1280.5057 870.1944) 
(list 1280.5057 870.2047) 
(list 1280.5057 870.215) 
(list 1280.5057 870.2253) 
(list 1280.5057 870.2356) 
(list 1280.5057 870.2458) 
(list 1280.5057 870.2561) 
(list 1280.5057 870.2664) 
(list 1280.5057 870.2767) 
(list 1280.5057 870.2869) 
(list 1280.5057 870.2972) 
(list 1280.5057 870.3075) 
(list 1280.5057 870.3178) 
(list 1280.5057 870.3281) 
(list 1280.5057 870.3383) 
(list 1280.5057 870.3486) 
(list 1280.5057 870.3589) 
(list 1280.5057 870.3692) 
(list 1280.5057 870.3794) 
(list 1280.5057 870.3897) 
(list 1280.5057 870.4) 
(list 1281.112 870.4)))
(apply 'command (append '("pline") coords '("c")))
(setq tap4 (ssadd (entlast) tap4))
(command "_mirror" (entlast) "" "1280,900" "1280,901" "No")
(setq tap4 (ssadd (entlast) tap4))
(setq coords (list 
(list 1280 870.4) 
(list 1280.125 870.4) 
(list 1280.125 870.4103) 
(list 1280.125 870.4206) 
(list 1280.125 870.4308) 
(list 1280.125 870.4411) 
(list 1280.125 870.4514) 
(list 1280.125 870.4617) 
(list 1280.125 870.4719) 
(list 1280.125 870.4822) 
(list 1280.125 870.4925) 
(list 1280.125 870.5028) 
(list 1280.125 870.5131) 
(list 1280.125 870.5233) 
(list 1280.125 870.5336) 
(list 1280.125 870.5439) 
(list 1280.125 870.5542) 
(list 1280.125 870.5644) 
(list 1280.125 870.5747) 
(list 1280.125 870.585) 
(list 1280.125 870.5953) 
(list 1280.125 870.6056) 
(list 1280.125 870.6158) 
(list 1280.125 870.6261) 
(list 1280.125 870.6364) 
(list 1280.125 870.6467) 
(list 1280.125 870.6569) 
(list 1280.125 870.6672) 
(list 1280.125 870.6775) 
(list 1280.125 870.6878) 
(list 1280.125 870.6981) 
(list 1280.125 870.7083) 
(list 1280.125 870.7186) 
(list 1280.125 870.7289) 
(list 1280.125 870.7392) 
(list 1280.125 870.7494) 
(list 1280.125 870.7597) 
(list 1280.125 870.77) 
(list 1280 870.77)))
(apply 'command (append '("pline") coords '("c")))
(setq tap4 (ssadd (entlast) tap4))
(command "_mirror" (entlast) "" "1280,900" "1280,901" "No")
(setq tap4 (ssadd (entlast) tap4))
(setq coords (list 
(list 1280.5157 870.4) 
(list 1280.5057 870.4) 
(list 1280.5045 870.4103) 
(list 1280.5005 870.4206) 
(list 1280.4937 870.4308) 
(list 1280.4844 870.4411) 
(list 1280.4728 870.4514) 
(list 1280.4592 870.4617) 
(list 1280.4441 870.4719) 
(list 1280.4279 870.4822) 
(list 1280.4111 870.4925) 
(list 1280.3943 870.5028) 
(list 1280.3778 870.5131) 
(list 1280.3623 870.5233) 
(list 1280.3482 870.5336) 
(list 1280.3359 870.5439) 
(list 1280.3258 870.5542) 
(list 1280.3184 870.5644) 
(list 1280.3137 870.5747) 
(list 1280.3119 870.585) 
(list 1280.3132 870.5953) 
(list 1280.3174 870.6056) 
(list 1280.3246 870.6158) 
(list 1280.3344 870.6261) 
(list 1280.3466 870.6364) 
(list 1280.3609 870.6467) 
(list 1280.3768 870.6569) 
(list 1280.3938 870.6672) 
(list 1280.4115 870.6775) 
(list 1280.4292 870.6878) 
(list 1280.4465 870.6981) 
(list 1280.4628 870.7083) 
(list 1280.4776 870.7186) 
(list 1280.4905 870.7289) 
(list 1280.501 870.7392) 
(list 1280.5089 870.7494) 
(list 1280.5139 870.7597) 
(list 1280.5157 870.77) 
(list 1280.5157 870.77)))
(apply 'command (append '("pline") coords '("c")))
(setq tap4 (ssadd (entlast) tap4))
(command "_mirror" (entlast) "" "1280,900" "1280,901" "No")
(setq tap4 (ssadd (entlast) tap4))
(setq coords (list 
(list 1281.112 870.4) 
(list 1280.5157 870.4) 
(list 1280.5157 870.4103) 
(list 1280.5157 870.4206) 
(list 1280.5157 870.4308) 
(list 1280.5157 870.4411) 
(list 1280.5157 870.4514) 
(list 1280.5157 870.4617) 
(list 1280.5157 870.4719) 
(list 1280.5157 870.4822) 
(list 1280.5157 870.4925) 
(list 1280.5157 870.5028) 
(list 1280.5157 870.5131) 
(list 1280.5157 870.5233) 
(list 1280.5157 870.5336) 
(list 1280.5157 870.5439) 
(list 1280.5157 870.5542) 
(list 1280.5157 870.5644) 
(list 1280.5157 870.5747) 
(list 1280.5157 870.585) 
(list 1280.5157 870.5953) 
(list 1280.5157 870.6056) 
(list 1280.5157 870.6158) 
(list 1280.5157 870.6261) 
(list 1280.5157 870.6364) 
(list 1280.5157 870.6467) 
(list 1280.5157 870.6569) 
(list 1280.5157 870.6672) 
(list 1280.5157 870.6775) 
(list 1280.5157 870.6878) 
(list 1280.5157 870.6981) 
(list 1280.5157 870.7083) 
(list 1280.5157 870.7186) 
(list 1280.5157 870.7289) 
(list 1280.5157 870.7392) 
(list 1280.5157 870.7494) 
(list 1280.5157 870.7597) 
(list 1280.5157 870.77) 
(list 1281.112 870.77)))
(apply 'command (append '("pline") coords '("c")))
(setq tap4 (ssadd (entlast) tap4))
(command "_mirror" (entlast) "" "1280,900" "1280,901" "No")
(setq tap4 (ssadd (entlast) tap4))
(setq coords (list 
(list 1280 870.77) 
(list 1280.125 870.77) 
(list 1280.125 870.7803) 
(list 1280.125 870.7906) 
(list 1280.125 870.8008) 
(list 1280.125 870.8111) 
(list 1280.125 870.8214) 
(list 1280.125 870.8317) 
(list 1280.125 870.8419) 
(list 1280.125 870.8522) 
(list 1280.125 870.8625) 
(list 1280.125 870.8728) 
(list 1280.125 870.8831) 
(list 1280.125 870.8933) 
(list 1280.125 870.9036) 
(list 1280.125 870.9139) 
(list 1280.125 870.9242) 
(list 1280.125 870.9344) 
(list 1280.125 870.9447) 
(list 1280.125 870.955) 
(list 1280.125 870.9653) 
(list 1280.125 870.9756) 
(list 1280.125 870.9858) 
(list 1280.125 870.9961) 
(list 1280.125 871.0064) 
(list 1280.125 871.0167) 
(list 1280.125 871.0269) 
(list 1280.125 871.0372) 
(list 1280.125 871.0475) 
(list 1280.125 871.0578) 
(list 1280.125 871.0681) 
(list 1280.125 871.0783) 
(list 1280.125 871.0886) 
(list 1280.125 871.0989) 
(list 1280.125 871.1092) 
(list 1280.125 871.1194) 
(list 1280.125 871.1297) 
(list 1280.125 871.14) 
(list 1280 871.14)))
(apply 'command (append '("pline") coords '("c")))
(setq tap4 (ssadd (entlast) tap4))
(command "_mirror" (entlast) "" "1280,900" "1280,901" "No")
(setq tap4 (ssadd (entlast) tap4))
(setq coords (list 
(list 1280.5258 870.77) 
(list 1280.5157 870.77) 
(list 1280.5144 870.7803) 
(list 1280.51 870.7906) 
(list 1280.5025 870.8008) 
(list 1280.4922 870.8111) 
(list 1280.4795 870.8214) 
(list 1280.4646 870.8317) 
(list 1280.448 870.8419) 
(list 1280.4302 870.8522) 
(list 1280.4117 870.8625) 
(list 1280.3932 870.8728) 
(list 1280.3752 870.8831) 
(list 1280.3582 870.8933) 
(list 1280.3427 870.9036) 
(list 1280.3292 870.9139) 
(list 1280.3183 870.9242) 
(list 1280.3101 870.9344) 
(list 1280.3049 870.9447) 
(list 1280.303 870.955) 
(list 1280.3044 870.9653) 
(list 1280.3091 870.9756) 
(list 1280.317 870.9858) 
(list 1280.3278 870.9961) 
(list 1280.3412 871.0064) 
(list 1280.3568 871.0167) 
(list 1280.3742 871.0269) 
(list 1280.3928 871.0372) 
(list 1280.412 871.0475) 
(list 1280.4314 871.0578) 
(list 1280.4503 871.0681) 
(list 1280.4681 871.0783) 
(list 1280.4843 871.0886) 
(list 1280.4984 871.0989) 
(list 1280.5098 871.1092) 
(list 1280.5184 871.1194) 
(list 1280.5238 871.1297) 
(list 1280.5258 871.14) 
(list 1280.5258 871.14)))
(apply 'command (append '("pline") coords '("c")))
(setq tap4 (ssadd (entlast) tap4))
(command "_mirror" (entlast) "" "1280,900" "1280,901" "No")
(setq tap4 (ssadd (entlast) tap4))
(setq coords (list 
(list 1281.112 870.77) 
(list 1280.5258 870.77) 
(list 1280.5258 870.7803) 
(list 1280.5258 870.7906) 
(list 1280.5258 870.8008) 
(list 1280.5258 870.8111) 
(list 1280.5258 870.8214) 
(list 1280.5258 870.8317) 
(list 1280.5258 870.8419) 
(list 1280.5258 870.8522) 
(list 1280.5258 870.8625) 
(list 1280.5258 870.8728) 
(list 1280.5258 870.8831) 
(list 1280.5258 870.8933) 
(list 1280.5258 870.9036) 
(list 1280.5258 870.9139) 
(list 1280.5258 870.9242) 
(list 1280.5258 870.9344) 
(list 1280.5258 870.9447) 
(list 1280.5258 870.955) 
(list 1280.5258 870.9653) 
(list 1280.5258 870.9756) 
(list 1280.5258 870.9858) 
(list 1280.5258 870.9961) 
(list 1280.5258 871.0064) 
(list 1280.5258 871.0167) 
(list 1280.5258 871.0269) 
(list 1280.5258 871.0372) 
(list 1280.5258 871.0475) 
(list 1280.5258 871.0578) 
(list 1280.5258 871.0681) 
(list 1280.5258 871.0783) 
(list 1280.5258 871.0886) 
(list 1280.5258 871.0989) 
(list 1280.5258 871.1092) 
(list 1280.5258 871.1194) 
(list 1280.5258 871.1297) 
(list 1280.5258 871.14) 
(list 1281.112 871.14)))
(apply 'command (append '("pline") coords '("c")))
(setq tap4 (ssadd (entlast) tap4))
(command "_mirror" (entlast) "" "1280,900" "1280,901" "No")
(setq tap4 (ssadd (entlast) tap4))
(setq coords (list 
(list 1280 871.14) 
(list 1280.125 871.14) 
(list 1280.125 871.1503) 
(list 1280.125 871.1606) 
(list 1280.125 871.1708) 
(list 1280.125 871.1811) 
(list 1280.125 871.1914) 
(list 1280.125 871.2017) 
(list 1280.125 871.2119) 
(list 1280.125 871.2222) 
(list 1280.125 871.2325) 
(list 1280.125 871.2428) 
(list 1280.125 871.2531) 
(list 1280.125 871.2633) 
(list 1280.125 871.2736) 
(list 1280.125 871.2839) 
(list 1280.125 871.2942) 
(list 1280.125 871.3044) 
(list 1280.125 871.3147) 
(list 1280.125 871.325) 
(list 1280.125 871.3353) 
(list 1280.125 871.3456) 
(list 1280.125 871.3558) 
(list 1280.125 871.3661) 
(list 1280.125 871.3764) 
(list 1280.125 871.3867) 
(list 1280.125 871.3969) 
(list 1280.125 871.4072) 
(list 1280.125 871.4175) 
(list 1280.125 871.4278) 
(list 1280.125 871.4381) 
(list 1280.125 871.4483) 
(list 1280.125 871.4586) 
(list 1280.125 871.4689) 
(list 1280.125 871.4792) 
(list 1280.125 871.4894) 
(list 1280.125 871.4997) 
(list 1280.125 871.51) 
(list 1280 871.51)))
(apply 'command (append '("pline") coords '("c")))
(setq tap4 (ssadd (entlast) tap4))
(command "_mirror" (entlast) "" "1280,900" "1280,901" "No")
(setq tap4 (ssadd (entlast) tap4))
(setq coords (list 
(list 1280.5359 871.14) 
(list 1280.5258 871.14) 
(list 1280.5243 871.1503) 
(list 1280.5195 871.1606) 
(list 1280.5113 871.1708) 
(list 1280.5001 871.1811) 
(list 1280.4861 871.1914) 
(list 1280.4699 871.2017) 
(list 1280.4518 871.2119) 
(list 1280.4324 871.2222) 
(list 1280.4124 871.2325) 
(list 1280.3922 871.2428) 
(list 1280.3725 871.2531) 
(list 1280.354 871.2633) 
(list 1280.3372 871.2736) 
(list 1280.3226 871.2839) 
(list 1280.3107 871.2942) 
(list 1280.3018 871.3044) 
(list 1280.2962 871.3147) 
(list 1280.2942 871.325) 
(list 1280.2957 871.3353) 
(list 1280.3008 871.3456) 
(list 1280.3094 871.3558) 
(list 1280.3211 871.3661) 
(list 1280.3357 871.3764) 
(list 1280.3526 871.3867) 
(list 1280.3715 871.3969) 
(list 1280.3917 871.4072) 
(list 1280.4126 871.4175) 
(list 1280.4337 871.4278) 
(list 1280.4541 871.4381) 
(list 1280.4734 871.4483) 
(list 1280.491 871.4586) 
(list 1280.5062 871.4689) 
(list 1280.5186 871.4792) 
(list 1280.5279 871.4894) 
(list 1280.5337 871.4997) 
(list 1280.5359 871.51) 
(list 1280.5359 871.51)))
(apply 'command (append '("pline") coords '("c")))
(setq tap4 (ssadd (entlast) tap4))
(command "_mirror" (entlast) "" "1280,900" "1280,901" "No")
(setq tap4 (ssadd (entlast) tap4))
(setq coords (list 
(list 1281.112 871.14) 
(list 1280.5359 871.14) 
(list 1280.5359 871.1503) 
(list 1280.5359 871.1606) 
(list 1280.5359 871.1708) 
(list 1280.5359 871.1811) 
(list 1280.5359 871.1914) 
(list 1280.5359 871.2017) 
(list 1280.5359 871.2119) 
(list 1280.5359 871.2222) 
(list 1280.5359 871.2325) 
(list 1280.5359 871.2428) 
(list 1280.5359 871.2531) 
(list 1280.5359 871.2633) 
(list 1280.5359 871.2736) 
(list 1280.5359 871.2839) 
(list 1280.5359 871.2942) 
(list 1280.5359 871.3044) 
(list 1280.5359 871.3147) 
(list 1280.5359 871.325) 
(list 1280.5359 871.3353) 
(list 1280.5359 871.3456) 
(list 1280.5359 871.3558) 
(list 1280.5359 871.3661) 
(list 1280.5359 871.3764) 
(list 1280.5359 871.3867) 
(list 1280.5359 871.3969) 
(list 1280.5359 871.4072) 
(list 1280.5359 871.4175) 
(list 1280.5359 871.4278) 
(list 1280.5359 871.4381) 
(list 1280.5359 871.4483) 
(list 1280.5359 871.4586) 
(list 1280.5359 871.4689) 
(list 1280.5359 871.4792) 
(list 1280.5359 871.4894) 
(list 1280.5359 871.4997) 
(list 1280.5359 871.51) 
(list 1281.112 871.51)))
(apply 'command (append '("pline") coords '("c")))
(setq tap4 (ssadd (entlast) tap4))
(command "_mirror" (entlast) "" "1280,900" "1280,901" "No")
(setq tap4 (ssadd (entlast) tap4))
(setq coords (list 
(list 1280 871.51) 
(list 1280.125 871.51) 
(list 1280.125 871.5203) 
(list 1280.125 871.5306) 
(list 1280.125 871.5408) 
(list 1280.125 871.5511) 
(list 1280.125 871.5614) 
(list 1280.125 871.5717) 
(list 1280.125 871.5819) 
(list 1280.125 871.5922) 
(list 1280.125 871.6025) 
(list 1280.125 871.6128) 
(list 1280.125 871.6231) 
(list 1280.125 871.6333) 
(list 1280.125 871.6436) 
(list 1280.125 871.6539) 
(list 1280.125 871.6642) 
(list 1280.125 871.6744) 
(list 1280.125 871.6847) 
(list 1280.125 871.695) 
(list 1280.125 871.7053) 
(list 1280.125 871.7156) 
(list 1280.125 871.7258) 
(list 1280.125 871.7361) 
(list 1280.125 871.7464) 
(list 1280.125 871.7567) 
(list 1280.125 871.7669) 
(list 1280.125 871.7772) 
(list 1280.125 871.7875) 
(list 1280.125 871.7978) 
(list 1280.125 871.8081) 
(list 1280.125 871.8183) 
(list 1280.125 871.8286) 
(list 1280.125 871.8389) 
(list 1280.125 871.8492) 
(list 1280.125 871.8594) 
(list 1280.125 871.8697) 
(list 1280.125 871.88) 
(list 1280 871.88)))
(apply 'command (append '("pline") coords '("c")))
(setq tap4 (ssadd (entlast) tap4))
(command "_mirror" (entlast) "" "1280,900" "1280,901" "No")
(setq tap4 (ssadd (entlast) tap4))
(setq coords (list 
(list 1280.5459 871.51) 
(list 1280.5359 871.51) 
(list 1280.5343 871.5203) 
(list 1280.529 871.5306) 
(list 1280.5201 871.5408) 
(list 1280.5079 871.5511) 
(list 1280.4928 871.5614) 
(list 1280.4752 871.5717) 
(list 1280.4556 871.5819) 
(list 1280.4347 871.5922) 
(list 1280.4129 871.6025) 
(list 1280.3911 871.6128) 
(list 1280.3699 871.6231) 
(list 1280.3499 871.6333) 
(list 1280.3317 871.6436) 
(list 1280.3159 871.6539) 
(list 1280.3031 871.6642) 
(list 1280.2935 871.6744) 
(list 1280.2875 871.6847) 
(list 1280.2853 871.695) 
(list 1280.287 871.7053) 
(list 1280.2925 871.7156) 
(list 1280.3018 871.7258) 
(list 1280.3145 871.7361) 
(list 1280.3302 871.7464) 
(list 1280.3485 871.7567) 
(list 1280.3689 871.7669) 
(list 1280.3907 871.7772) 
(list 1280.4133 871.7875) 
(list 1280.4359 871.7978) 
(list 1280.458 871.8081) 
(list 1280.4788 871.8183) 
(list 1280.4977 871.8286) 
(list 1280.5141 871.8389) 
(list 1280.5274 871.8492) 
(list 1280.5374 871.8594) 
(list 1280.5436 871.8697) 
(list 1280.5459 871.88) 
(list 1280.5459 871.88)))
(apply 'command (append '("pline") coords '("c")))
(setq tap4 (ssadd (entlast) tap4))
(command "_mirror" (entlast) "" "1280,900" "1280,901" "No")
(setq tap4 (ssadd (entlast) tap4))
(setq coords (list 
(list 1281.112 871.51) 
(list 1280.5459 871.51) 
(list 1280.5459 871.5203) 
(list 1280.5459 871.5306) 
(list 1280.5459 871.5408) 
(list 1280.5459 871.5511) 
(list 1280.5459 871.5614) 
(list 1280.5459 871.5717) 
(list 1280.5459 871.5819) 
(list 1280.5459 871.5922) 
(list 1280.5459 871.6025) 
(list 1280.5459 871.6128) 
(list 1280.5459 871.6231) 
(list 1280.5459 871.6333) 
(list 1280.5459 871.6436) 
(list 1280.5459 871.6539) 
(list 1280.5459 871.6642) 
(list 1280.5459 871.6744) 
(list 1280.5459 871.6847) 
(list 1280.5459 871.695) 
(list 1280.5459 871.7053) 
(list 1280.5459 871.7156) 
(list 1280.5459 871.7258) 
(list 1280.5459 871.7361) 
(list 1280.5459 871.7464) 
(list 1280.5459 871.7567) 
(list 1280.5459 871.7669) 
(list 1280.5459 871.7772) 
(list 1280.5459 871.7875) 
(list 1280.5459 871.7978) 
(list 1280.5459 871.8081) 
(list 1280.5459 871.8183) 
(list 1280.5459 871.8286) 
(list 1280.5459 871.8389) 
(list 1280.5459 871.8492) 
(list 1280.5459 871.8594) 
(list 1280.5459 871.8697) 
(list 1280.5459 871.88) 
(list 1281.112 871.88)))
(apply 'command (append '("pline") coords '("c")))
(setq tap4 (ssadd (entlast) tap4))
(command "_mirror" (entlast) "" "1280,900" "1280,901" "No")
(setq tap4 (ssadd (entlast) tap4))
(setq coords (list 
(list 1280 871.88) 
(list 1280.125 871.88) 
(list 1280.125 871.8903) 
(list 1280.125 871.9006) 
(list 1280.125 871.9108) 
(list 1280.125 871.9211) 
(list 1280.125 871.9314) 
(list 1280.125 871.9417) 
(list 1280.125 871.9519) 
(list 1280.125 871.9622) 
(list 1280.125 871.9725) 
(list 1280.125 871.9828) 
(list 1280.125 871.9931) 
(list 1280.125 872.0033) 
(list 1280.125 872.0136) 
(list 1280.125 872.0239) 
(list 1280.125 872.0342) 
(list 1280.125 872.0444) 
(list 1280.125 872.0547) 
(list 1280.125 872.065) 
(list 1280.125 872.0753) 
(list 1280.125 872.0856) 
(list 1280.125 872.0958) 
(list 1280.125 872.1061) 
(list 1280.125 872.1164) 
(list 1280.125 872.1267) 
(list 1280.125 872.1369) 
(list 1280.125 872.1472) 
(list 1280.125 872.1575) 
(list 1280.125 872.1678) 
(list 1280.125 872.1781) 
(list 1280.125 872.1883) 
(list 1280.125 872.1986) 
(list 1280.125 872.2089) 
(list 1280.125 872.2192) 
(list 1280.125 872.2294) 
(list 1280.125 872.2397) 
(list 1280.125 872.25) 
(list 1280 872.25)))
(apply 'command (append '("pline") coords '("c")))
(setq tap4 (ssadd (entlast) tap4))
(command "_mirror" (entlast) "" "1280,900" "1280,901" "No")
(setq tap4 (ssadd (entlast) tap4))
(setq coords (list 
(list 1280.556 871.88) 
(list 1280.5459 871.88) 
(list 1280.5442 871.8903) 
(list 1280.5385 871.9006) 
(list 1280.5289 871.9108) 
(list 1280.5158 871.9211) 
(list 1280.4995 871.9314) 
(list 1280.4806 871.9417) 
(list 1280.4595 871.9519) 
(list 1280.4369 871.9622) 
(list 1280.4135 871.9725) 
(list 1280.3901 871.9828) 
(list 1280.3673 871.9931) 
(list 1280.3458 872.0033) 
(list 1280.3262 872.0136) 
(list 1280.3093 872.0239) 
(list 1280.2955 872.0342) 
(list 1280.2852 872.0444) 
(list 1280.2788 872.0547) 
(list 1280.2764 872.065) 
(list 1280.2783 872.0753) 
(list 1280.2842 872.0856) 
(list 1280.2942 872.0958) 
(list 1280.3078 872.1061) 
(list 1280.3247 872.1164) 
(list 1280.3444 872.1267) 
(list 1280.3662 872.1369) 
(list 1280.3896 872.1472) 
(list 1280.4138 872.1575) 
(list 1280.4382 872.1678) 
(list 1280.4618 872.1781) 
(list 1280.4841 872.1883) 
(list 1280.5043 872.1986) 
(list 1280.5219 872.2089) 
(list 1280.5362 872.2192) 
(list 1280.5469 872.2294) 
(list 1280.5536 872.2397) 
(list 1280.556 872.25) 
(list 1280.556 872.25)))
(apply 'command (append '("pline") coords '("c")))
(setq tap4 (ssadd (entlast) tap4))
(command "_mirror" (entlast) "" "1280,900" "1280,901" "No")
(setq tap4 (ssadd (entlast) tap4))
(setq coords (list 
(list 1281.112 871.88) 
(list 1280.556 871.88) 
(list 1280.556 871.8903) 
(list 1280.556 871.9006) 
(list 1280.556 871.9108) 
(list 1280.556 871.9211) 
(list 1280.556 871.9314) 
(list 1280.556 871.9417) 
(list 1280.556 871.9519) 
(list 1280.556 871.9622) 
(list 1280.556 871.9725) 
(list 1280.556 871.9828) 
(list 1280.556 871.9931) 
(list 1280.556 872.0033) 
(list 1280.556 872.0136) 
(list 1280.556 872.0239) 
(list 1280.556 872.0342) 
(list 1280.556 872.0444) 
(list 1280.556 872.0547) 
(list 1280.556 872.065) 
(list 1280.556 872.0753) 
(list 1280.556 872.0856) 
(list 1280.556 872.0958) 
(list 1280.556 872.1061) 
(list 1280.556 872.1164) 
(list 1280.556 872.1267) 
(list 1280.556 872.1369) 
(list 1280.556 872.1472) 
(list 1280.556 872.1575) 
(list 1280.556 872.1678) 
(list 1280.556 872.1781) 
(list 1280.556 872.1883) 
(list 1280.556 872.1986) 
(list 1280.556 872.2089) 
(list 1280.556 872.2192) 
(list 1280.556 872.2294) 
(list 1280.556 872.2397) 
(list 1280.556 872.25) 
(list 1281.112 872.25)))
(apply 'command (append '("pline") coords '("c")))
(setq tap4 (ssadd (entlast) tap4))
(command "_mirror" (entlast) "" "1280,900" "1280,901" "No")
(setq tap4 (ssadd (entlast) tap4))
(command "_block" "blktap4" "1280,900" tap4 "")
(command "_insert" "blktap4" "1280,900" "1" "1" "0")
(command "_insert" "blktap4" "1280,900" "1" "1" "180")
(setq uc4 nil)
(setq uc4 (ssadd))
(setq coords (list 
(list 0 -0.185) 
(list 0.125 -0.185) 
(list 0.125 -0.17472) 
(list 0.125 -0.16444) 
(list 0.125 -0.15417) 
(list 0.125 -0.14389) 
(list 0.125 -0.13361) 
(list 0.125 -0.12333) 
(list 0.125 -0.11306) 
(list 0.125 -0.10278) 
(list 0.125 -0.0925) 
(list 0.125 -0.082222) 
(list 0.125 -0.071944) 
(list 0.125 -0.061667) 
(list 0.125 -0.051389) 
(list 0.125 -0.041111) 
(list 0.125 -0.030833) 
(list 0.125 -0.020556) 
(list 0.125 -0.010278) 
(list 0.125 0) 
(list 0.125 0.010278) 
(list 0.125 0.020556) 
(list 0.125 0.030833) 
(list 0.125 0.041111) 
(list 0.125 0.051389) 
(list 0.125 0.061667) 
(list 0.125 0.071944) 
(list 0.125 0.082222) 
(list 0.125 0.0925) 
(list 0.125 0.10278) 
(list 0.125 0.11306) 
(list 0.125 0.12333) 
(list 0.125 0.13361) 
(list 0.125 0.14389) 
(list 0.125 0.15417) 
(list 0.125 0.16444) 
(list 0.125 0.17472) 
(list 0.125 0.185) 
(list 0 0.185)))
(apply 'command (append '("pline") coords '("c")))
(setq uc4 (ssadd (entlast) uc4))
(setq coords (list 
(list 1.112 -0.185) 
(list 0.556 -0.185) 
(list 0.55384 -0.17472) 
(list 0.54744 -0.16444) 
(list 0.53698 -0.15417) 
(list 0.52278 -0.14389) 
(list 0.50528 -0.13361) 
(list 0.485 -0.12333) 
(list 0.46257 -0.11306) 
(list 0.43866 -0.10278) 
(list 0.414 -0.0925) 
(list 0.38934 -0.082222) 
(list 0.36543 -0.071944) 
(list 0.343 -0.061667) 
(list 0.32272 -0.051389) 
(list 0.30522 -0.041111) 
(list 0.29102 -0.030833) 
(list 0.28056 -0.020556) 
(list 0.27416 -0.010278) 
(list 0.272 0) 
(list 0.27416 0.010278) 
(list 0.28056 0.020556) 
(list 0.29102 0.030833) 
(list 0.30522 0.041111) 
(list 0.32272 0.051389) 
(list 0.343 0.061667) 
(list 0.36543 0.071944) 
(list 0.38934 0.082222) 
(list 0.414 0.0925) 
(list 0.43866 0.10278) 
(list 0.46257 0.11306) 
(list 0.485 0.12333) 
(list 0.50528 0.13361) 
(list 0.52278 0.14389) 
(list 0.53698 0.15417) 
(list 0.54744 0.16444) 
(list 0.55384 0.17472) 
(list 0.556 0.185) 
(list 1.112 0.185)))
(apply 'command (append '("pline") coords '("c")))
(setq uc4 (ssadd (entlast) uc4))
(command "_block" "blkuc4" "0,0.185" uc4 "")
(command "_insert" "blkuc4" "1280,872.62" "1" "1" "0")
(command "_insert" "blkuc4" "1280,872.25" "1" "1" "180")
(command "_insert" "blkuc4" "1280,872.99" "1" "1" "0")
(command "_insert" "blkuc4" "1280,872.62" "1" "1" "180")
(command "_insert" "blkuc4" "1280,873.36" "1" "1" "0")
(command "_insert" "blkuc4" "1280,872.99" "1" "1" "180")
(command "_insert" "blkuc4" "1280,873.73" "1" "1" "0")
(command "_insert" "blkuc4" "1280,873.36" "1" "1" "180")
(command "_insert" "blkuc4" "1280,874.1" "1" "1" "0")
(command "_insert" "blkuc4" "1280,873.73" "1" "1" "180")
(command "_insert" "blkuc4" "1280,874.47" "1" "1" "0")
(command "_insert" "blkuc4" "1280,874.1" "1" "1" "180")
(command "_insert" "blkuc4" "1280,874.84" "1" "1" "0")
(command "_insert" "blkuc4" "1280,874.47" "1" "1" "180")
(command "_insert" "blkuc4" "1280,875.21" "1" "1" "0")
(command "_insert" "blkuc4" "1280,874.84" "1" "1" "180")
(command "_insert" "blkuc4" "1280,875.58" "1" "1" "0")
(command "_insert" "blkuc4" "1280,875.21" "1" "1" "180")
(command "_insert" "blkuc4" "1280,875.95" "1" "1" "0")
(command "_insert" "blkuc4" "1280,875.58" "1" "1" "180")
(command "_insert" "blkuc4" "1280,876.32" "1" "1" "0")
(command "_insert" "blkuc4" "1280,875.95" "1" "1" "180")
(command "_insert" "blkuc4" "1280,876.69" "1" "1" "0")
(command "_insert" "blkuc4" "1280,876.32" "1" "1" "180")
(command "_insert" "blkuc4" "1280,877.06" "1" "1" "0")
(command "_insert" "blkuc4" "1280,876.69" "1" "1" "180")
(command "_insert" "blkuc4" "1280,877.43" "1" "1" "0")
(command "_insert" "blkuc4" "1280,877.06" "1" "1" "180")
(command "_insert" "blkuc4" "1280,877.8" "1" "1" "0")
(command "_insert" "blkuc4" "1280,877.43" "1" "1" "180")
(command "_insert" "blkuc4" "1280,878.17" "1" "1" "0")
(command "_insert" "blkuc4" "1280,877.8" "1" "1" "180")
(command "_insert" "blkuc4" "1280,878.54" "1" "1" "0")
(command "_insert" "blkuc4" "1280,878.17" "1" "1" "180")
(command "_insert" "blkuc4" "1280,878.91" "1" "1" "0")
(command "_insert" "blkuc4" "1280,878.54" "1" "1" "180")
(command "_insert" "blkuc4" "1280,879.28" "1" "1" "0")
(command "_insert" "blkuc4" "1280,878.91" "1" "1" "180")
(command "_insert" "blkuc4" "1280,879.65" "1" "1" "0")
(command "_insert" "blkuc4" "1280,879.28" "1" "1" "180")
(command "_insert" "blkuc4" "1280,880.02" "1" "1" "0")
(command "_insert" "blkuc4" "1280,879.65" "1" "1" "180")
(command "_insert" "blkuc4" "1280,880.39" "1" "1" "0")
(command "_insert" "blkuc4" "1280,880.02" "1" "1" "180")
(command "_insert" "blkuc4" "1280,880.76" "1" "1" "0")
(command "_insert" "blkuc4" "1280,880.39" "1" "1" "180")
(command "_insert" "blkuc4" "1280,881.13" "1" "1" "0")
(command "_insert" "blkuc4" "1280,880.76" "1" "1" "180")
(command "_insert" "blkuc4" "1280,881.5" "1" "1" "0")
(command "_insert" "blkuc4" "1280,881.13" "1" "1" "180")
(command "_insert" "blkuc4" "1280,881.87" "1" "1" "0")
(command "_insert" "blkuc4" "1280,881.5" "1" "1" "180")
(command "_insert" "blkuc4" "1280,882.24" "1" "1" "0")
(command "_insert" "blkuc4" "1280,881.87" "1" "1" "180")
(command "_insert" "blkuc4" "1280,882.61" "1" "1" "0")
(command "_insert" "blkuc4" "1280,882.24" "1" "1" "180")
(command "_insert" "blkuc4" "1280,882.98" "1" "1" "0")
(command "_insert" "blkuc4" "1280,882.61" "1" "1" "180")
(command "_insert" "blkuc4" "1280,883.35" "1" "1" "0")
(command "_insert" "blkuc4" "1280,882.98" "1" "1" "180")
(command "_insert" "blkuc4" "1280,883.72" "1" "1" "0")
(command "_insert" "blkuc4" "1280,883.35" "1" "1" "180")
(command "_insert" "blkuc4" "1280,884.09" "1" "1" "0")
(command "_insert" "blkuc4" "1280,883.72" "1" "1" "180")
(command "_insert" "blkuc4" "1280,884.46" "1" "1" "0")
(command "_insert" "blkuc4" "1280,884.09" "1" "1" "180")
(command "_insert" "blkuc4" "1280,884.83" "1" "1" "0")
(command "_insert" "blkuc4" "1280,884.46" "1" "1" "180")
(command "_insert" "blkuc4" "1280,885.2" "1" "1" "0")
(command "_insert" "blkuc4" "1280,884.83" "1" "1" "180")
(command "_insert" "blkuc4" "1280,885.57" "1" "1" "0")
(command "_insert" "blkuc4" "1280,885.2" "1" "1" "180")
(command "_insert" "blkuc4" "1280,885.94" "1" "1" "0")
(command "_insert" "blkuc4" "1280,885.57" "1" "1" "180")
(command "_insert" "blkuc4" "1280,886.31" "1" "1" "0")
(command "_insert" "blkuc4" "1280,885.94" "1" "1" "180")
(command "_insert" "blkuc4" "1280,886.68" "1" "1" "0")
(command "_insert" "blkuc4" "1280,886.31" "1" "1" "180")
(command "_insert" "blkuc4" "1280,887.05" "1" "1" "0")
(command "_insert" "blkuc4" "1280,886.68" "1" "1" "180")
(command "_insert" "blkuc4" "1280,887.42" "1" "1" "0")
(command "_insert" "blkuc4" "1280,887.05" "1" "1" "180")
(command "_insert" "blkuc4" "1280,887.79" "1" "1" "0")
(command "_insert" "blkuc4" "1280,887.42" "1" "1" "180")
(command "_insert" "blkuc4" "1280,888.16" "1" "1" "0")
(command "_insert" "blkuc4" "1280,887.79" "1" "1" "180")
(command "_insert" "blkuc4" "1280,888.53" "1" "1" "0")
(command "_insert" "blkuc4" "1280,888.16" "1" "1" "180")
(command "_insert" "blkuc4" "1280,888.9" "1" "1" "0")
(command "_insert" "blkuc4" "1280,888.53" "1" "1" "180")
(command "_insert" "blkuc4" "1280,889.27" "1" "1" "0")
(command "_insert" "blkuc4" "1280,888.9" "1" "1" "180")
(command "_insert" "blkuc4" "1280,889.64" "1" "1" "0")
(command "_insert" "blkuc4" "1280,889.27" "1" "1" "180")
(command "_insert" "blkuc4" "1280,890.01" "1" "1" "0")
(command "_insert" "blkuc4" "1280,889.64" "1" "1" "180")
(command "_insert" "blkuc4" "1280,890.38" "1" "1" "0")
(command "_insert" "blkuc4" "1280,890.01" "1" "1" "180")
(command "_insert" "blkuc4" "1280,890.75" "1" "1" "0")
(command "_insert" "blkuc4" "1280,890.38" "1" "1" "180")
(command "_insert" "blkuc4" "1280,891.12" "1" "1" "0")
(command "_insert" "blkuc4" "1280,890.75" "1" "1" "180")
(command "_insert" "blkuc4" "1280,891.49" "1" "1" "0")
(command "_insert" "blkuc4" "1280,891.12" "1" "1" "180")
(command "_insert" "blkuc4" "1280,891.86" "1" "1" "0")
(command "_insert" "blkuc4" "1280,891.49" "1" "1" "180")
(command "_insert" "blkuc4" "1280,892.23" "1" "1" "0")
(command "_insert" "blkuc4" "1280,891.86" "1" "1" "180")
(command "_insert" "blkuc4" "1280,892.6" "1" "1" "0")
(command "_insert" "blkuc4" "1280,892.23" "1" "1" "180")
(command "_insert" "blkuc4" "1280,892.97" "1" "1" "0")
(command "_insert" "blkuc4" "1280,892.6" "1" "1" "180")
(command "_insert" "blkuc4" "1280,893.34" "1" "1" "0")
(command "_insert" "blkuc4" "1280,892.97" "1" "1" "180")
(command "_insert" "blkuc4" "1280,893.71" "1" "1" "0")
(command "_insert" "blkuc4" "1280,893.34" "1" "1" "180")
(command "_insert" "blkuc4" "1280,894.08" "1" "1" "0")
(command "_insert" "blkuc4" "1280,893.71" "1" "1" "180")
(command "_insert" "blkuc4" "1280,894.45" "1" "1" "0")
(command "_insert" "blkuc4" "1280,894.08" "1" "1" "180")
(command "_insert" "blkuc4" "1280,894.82" "1" "1" "0")
(command "_insert" "blkuc4" "1280,894.45" "1" "1" "180")
(command "_insert" "blkuc4" "1280,895.19" "1" "1" "0")
(command "_insert" "blkuc4" "1280,894.82" "1" "1" "180")
(command "_insert" "blkuc4" "1280,895.56" "1" "1" "0")
(command "_insert" "blkuc4" "1280,895.19" "1" "1" "180")
(command "_insert" "blkuc4" "1280,895.93" "1" "1" "0")
(command "_insert" "blkuc4" "1280,895.56" "1" "1" "180")
(command "_insert" "blkuc4" "1280,896.3" "1" "1" "0")
(command "_insert" "blkuc4" "1280,895.93" "1" "1" "180")
(command "_insert" "blkuc4" "1280,896.67" "1" "1" "0")
(command "_insert" "blkuc4" "1280,896.3" "1" "1" "180")
(command "_insert" "blkuc4" "1280,897.04" "1" "1" "0")
(command "_insert" "blkuc4" "1280,896.67" "1" "1" "180")
(command "_insert" "blkuc4" "1280,897.41" "1" "1" "0")
(command "_insert" "blkuc4" "1280,897.04" "1" "1" "180")
(command "_insert" "blkuc4" "1280,897.78" "1" "1" "0")
(command "_insert" "blkuc4" "1280,897.41" "1" "1" "180")
(command "_insert" "blkuc4" "1280,898.15" "1" "1" "0")
(command "_insert" "blkuc4" "1280,897.78" "1" "1" "180")
(command "_insert" "blkuc4" "1280,898.52" "1" "1" "0")
(command "_insert" "blkuc4" "1280,898.15" "1" "1" "180")
(command "_insert" "blkuc4" "1280,898.89" "1" "1" "0")
(command "_insert" "blkuc4" "1280,898.52" "1" "1" "180")
(command "_insert" "blkuc4" "1280,899.26" "1" "1" "0")
(command "_insert" "blkuc4" "1280,898.89" "1" "1" "180")
(command "_insert" "blkuc4" "1280,899.63" "1" "1" "0")
(command "_insert" "blkuc4" "1280,899.26" "1" "1" "180")
(command "_insert" "blkuc4" "1280,900" "1" "1" "0")
(command "_insert" "blkuc4" "1280,899.63" "1" "1" "180")
(command "_insert" "blkuc4" "1280,900.37" "1" "1" "0")
(command "_insert" "blkuc4" "1280,900" "1" "1" "180")
(command "_insert" "blkuc4" "1280,900.74" "1" "1" "0")
(command "_insert" "blkuc4" "1280,900.37" "1" "1" "180")
(command "_insert" "blkuc4" "1280,901.11" "1" "1" "0")
(command "_insert" "blkuc4" "1280,900.74" "1" "1" "180")
(command "_insert" "blkuc4" "1280,901.48" "1" "1" "0")
(command "_insert" "blkuc4" "1280,901.11" "1" "1" "180")
(command "_insert" "blkuc4" "1280,901.85" "1" "1" "0")
(command "_insert" "blkuc4" "1280,901.48" "1" "1" "180")
(command "_insert" "blkuc4" "1280,902.22" "1" "1" "0")
(command "_insert" "blkuc4" "1280,901.85" "1" "1" "180")
(command "_insert" "blkuc4" "1280,902.59" "1" "1" "0")
(command "_insert" "blkuc4" "1280,902.22" "1" "1" "180")
(command "_insert" "blkuc4" "1280,902.96" "1" "1" "0")
(command "_insert" "blkuc4" "1280,902.59" "1" "1" "180")
(command "_insert" "blkuc4" "1280,903.33" "1" "1" "0")
(command "_insert" "blkuc4" "1280,902.96" "1" "1" "180")
(command "_insert" "blkuc4" "1280,903.7" "1" "1" "0")
(command "_insert" "blkuc4" "1280,903.33" "1" "1" "180")
(command "_insert" "blkuc4" "1280,904.07" "1" "1" "0")
(command "_insert" "blkuc4" "1280,903.7" "1" "1" "180")
(command "_insert" "blkuc4" "1280,904.44" "1" "1" "0")
(command "_insert" "blkuc4" "1280,904.07" "1" "1" "180")
(command "_insert" "blkuc4" "1280,904.81" "1" "1" "0")
(command "_insert" "blkuc4" "1280,904.44" "1" "1" "180")
(command "_insert" "blkuc4" "1280,905.18" "1" "1" "0")
(command "_insert" "blkuc4" "1280,904.81" "1" "1" "180")
(command "_insert" "blkuc4" "1280,905.55" "1" "1" "0")
(command "_insert" "blkuc4" "1280,905.18" "1" "1" "180")
(command "_insert" "blkuc4" "1280,905.92" "1" "1" "0")
(command "_insert" "blkuc4" "1280,905.55" "1" "1" "180")
(command "_insert" "blkuc4" "1280,906.29" "1" "1" "0")
(command "_insert" "blkuc4" "1280,905.92" "1" "1" "180")
(command "_insert" "blkuc4" "1280,906.66" "1" "1" "0")
(command "_insert" "blkuc4" "1280,906.29" "1" "1" "180")
(command "_insert" "blkuc4" "1280,907.03" "1" "1" "0")
(command "_insert" "blkuc4" "1280,906.66" "1" "1" "180")
(command "_insert" "blkuc4" "1280,907.4" "1" "1" "0")
(command "_insert" "blkuc4" "1280,907.03" "1" "1" "180")
(command "_insert" "blkuc4" "1280,907.77" "1" "1" "0")
(command "_insert" "blkuc4" "1280,907.4" "1" "1" "180")
(command "_insert" "blkuc4" "1280,908.14" "1" "1" "0")
(command "_insert" "blkuc4" "1280,907.77" "1" "1" "180")
(command "_insert" "blkuc4" "1280,908.51" "1" "1" "0")
(command "_insert" "blkuc4" "1280,908.14" "1" "1" "180")
(command "_insert" "blkuc4" "1280,908.88" "1" "1" "0")
(command "_insert" "blkuc4" "1280,908.51" "1" "1" "180")
(command "_insert" "blkuc4" "1280,909.25" "1" "1" "0")
(command "_insert" "blkuc4" "1280,908.88" "1" "1" "180")
(command "_insert" "blkuc4" "1280,909.62" "1" "1" "0")
(command "_insert" "blkuc4" "1280,909.25" "1" "1" "180")
(command "_insert" "blkuc4" "1280,909.99" "1" "1" "0")
(command "_insert" "blkuc4" "1280,909.62" "1" "1" "180")
(command "_insert" "blkuc4" "1280,910.36" "1" "1" "0")
(command "_insert" "blkuc4" "1280,909.99" "1" "1" "180")
(command "_insert" "blkuc4" "1280,910.73" "1" "1" "0")
(command "_insert" "blkuc4" "1280,910.36" "1" "1" "180")
(command "_insert" "blkuc4" "1280,911.1" "1" "1" "0")
(command "_insert" "blkuc4" "1280,910.73" "1" "1" "180")
(command "_insert" "blkuc4" "1280,911.47" "1" "1" "0")
(command "_insert" "blkuc4" "1280,911.1" "1" "1" "180")
(command "_insert" "blkuc4" "1280,911.84" "1" "1" "0")
(command "_insert" "blkuc4" "1280,911.47" "1" "1" "180")
(command "_insert" "blkuc4" "1280,912.21" "1" "1" "0")
(command "_insert" "blkuc4" "1280,911.84" "1" "1" "180")
(command "_insert" "blkuc4" "1280,912.58" "1" "1" "0")
(command "_insert" "blkuc4" "1280,912.21" "1" "1" "180")
(command "_insert" "blkuc4" "1280,912.95" "1" "1" "0")
(command "_insert" "blkuc4" "1280,912.58" "1" "1" "180")
(command "_insert" "blkuc4" "1280,913.32" "1" "1" "0")
(command "_insert" "blkuc4" "1280,912.95" "1" "1" "180")
(command "_insert" "blkuc4" "1280,913.69" "1" "1" "0")
(command "_insert" "blkuc4" "1280,913.32" "1" "1" "180")
(command "_insert" "blkuc4" "1280,914.06" "1" "1" "0")
(command "_insert" "blkuc4" "1280,913.69" "1" "1" "180")
(command "_insert" "blkuc4" "1280,914.43" "1" "1" "0")
(command "_insert" "blkuc4" "1280,914.06" "1" "1" "180")
(command "_insert" "blkuc4" "1280,914.8" "1" "1" "0")
(command "_insert" "blkuc4" "1280,914.43" "1" "1" "180")
(command "_insert" "blkuc4" "1280,915.17" "1" "1" "0")
(command "_insert" "blkuc4" "1280,914.8" "1" "1" "180")
(command "_insert" "blkuc4" "1280,915.54" "1" "1" "0")
(command "_insert" "blkuc4" "1280,915.17" "1" "1" "180")
(command "_insert" "blkuc4" "1280,915.91" "1" "1" "0")
(command "_insert" "blkuc4" "1280,915.54" "1" "1" "180")
(command "_insert" "blkuc4" "1280,916.28" "1" "1" "0")
(command "_insert" "blkuc4" "1280,915.91" "1" "1" "180")
(command "_insert" "blkuc4" "1280,916.65" "1" "1" "0")
(command "_insert" "blkuc4" "1280,916.28" "1" "1" "180")
(command "_insert" "blkuc4" "1280,917.02" "1" "1" "0")
(command "_insert" "blkuc4" "1280,916.65" "1" "1" "180")
(command "_insert" "blkuc4" "1280,917.39" "1" "1" "0")
(command "_insert" "blkuc4" "1280,917.02" "1" "1" "180")
(command "_insert" "blkuc4" "1280,917.76" "1" "1" "0")
(command "_insert" "blkuc4" "1280,917.39" "1" "1" "180")
(command "_insert" "blkuc4" "1280,918.13" "1" "1" "0")
(command "_insert" "blkuc4" "1280,917.76" "1" "1" "180")
(command "_insert" "blkuc4" "1280,918.5" "1" "1" "0")
(command "_insert" "blkuc4" "1280,918.13" "1" "1" "180")
(command "_insert" "blkuc4" "1280,918.87" "1" "1" "0")
(command "_insert" "blkuc4" "1280,918.5" "1" "1" "180")
(command "_insert" "blkuc4" "1280,919.24" "1" "1" "0")
(command "_insert" "blkuc4" "1280,918.87" "1" "1" "180")
(command "_insert" "blkuc4" "1280,919.61" "1" "1" "0")
(command "_insert" "blkuc4" "1280,919.24" "1" "1" "180")
(command "_insert" "blkuc4" "1280,919.98" "1" "1" "0")
(command "_insert" "blkuc4" "1280,919.61" "1" "1" "180")
(command "_insert" "blkuc4" "1280,920.35" "1" "1" "0")
(command "_insert" "blkuc4" "1280,919.98" "1" "1" "180")
(command "_insert" "blkuc4" "1280,920.72" "1" "1" "0")
(command "_insert" "blkuc4" "1280,920.35" "1" "1" "180")
(command "_insert" "blkuc4" "1280,921.09" "1" "1" "0")
(command "_insert" "blkuc4" "1280,920.72" "1" "1" "180")
(command "_insert" "blkuc4" "1280,921.46" "1" "1" "0")
(command "_insert" "blkuc4" "1280,921.09" "1" "1" "180")
(command "_insert" "blkuc4" "1280,921.83" "1" "1" "0")
(command "_insert" "blkuc4" "1280,921.46" "1" "1" "180")
(command "_insert" "blkuc4" "1280,922.2" "1" "1" "0")
(command "_insert" "blkuc4" "1280,921.83" "1" "1" "180")
(command "_insert" "blkuc4" "1280,922.57" "1" "1" "0")
(command "_insert" "blkuc4" "1280,922.2" "1" "1" "180")
(command "_insert" "blkuc4" "1280,922.94" "1" "1" "0")
(command "_insert" "blkuc4" "1280,922.57" "1" "1" "180")
(command "_insert" "blkuc4" "1280,923.31" "1" "1" "0")
(command "_insert" "blkuc4" "1280,922.94" "1" "1" "180")
(command "_insert" "blkuc4" "1280,923.68" "1" "1" "0")
(command "_insert" "blkuc4" "1280,923.31" "1" "1" "180")
(command "_insert" "blkuc4" "1280,924.05" "1" "1" "0")
(command "_insert" "blkuc4" "1280,923.68" "1" "1" "180")
(command "_insert" "blkuc4" "1280,924.42" "1" "1" "0")
(command "_insert" "blkuc4" "1280,924.05" "1" "1" "180")
(command "_insert" "blkuc4" "1280,924.79" "1" "1" "0")
(command "_insert" "blkuc4" "1280,924.42" "1" "1" "180")
(command "_insert" "blkuc4" "1280,925.16" "1" "1" "0")
(command "_insert" "blkuc4" "1280,924.79" "1" "1" "180")
(command "_insert" "blkuc4" "1280,925.53" "1" "1" "0")
(command "_insert" "blkuc4" "1280,925.16" "1" "1" "180")
(command "_insert" "blkuc4" "1280,925.9" "1" "1" "0")
(command "_insert" "blkuc4" "1280,925.53" "1" "1" "180")
(command "_insert" "blkuc4" "1280,926.27" "1" "1" "0")
(command "_insert" "blkuc4" "1280,925.9" "1" "1" "180")
(command "_insert" "blkuc4" "1280,926.64" "1" "1" "0")
(command "_insert" "blkuc4" "1280,926.27" "1" "1" "180")
(command "_insert" "blkuc4" "1280,927.01" "1" "1" "0")
(command "_insert" "blkuc4" "1280,926.64" "1" "1" "180")
(command "_insert" "blkuc4" "1280,927.38" "1" "1" "0")
(command "_insert" "blkuc4" "1280,927.01" "1" "1" "180")
(command "_insert" "blkuc4" "1280,927.75" "1" "1" "0")
(command "_insert" "blkuc4" "1280,927.38" "1" "1" "180")
(command "_layer" "set" "phccover" "")
(command "_rectangle" "1278.888,933.3" "1281.112,866.7")
(command "_layer" "set" "nitride" "")
(setq phc4 currobj)
(command "_layer" "set" "cover" "")
(command "_rectangle" "1278.888,836.7" "1281.112,963.3")
(command "_layer" "set" "nitride" "")
(command "_layer" "set" "text" "")
(command "_circle" "1277.938,846.7" "0.075")
(command "_circle" "1277.563,846.7" "0.15")
(command "_circle" "1277.188,846.7" "0.075")
(command "_circle" "1276.813,846.7" "0.15")
(command "_circle" "1277.938,848.7" "0.075")
(command "_circle" "1277.563,848.7" "0.075")
(command "_circle" "1277.188,848.7" "0.15")
(command "_circle" "1276.813,848.7" "0.15")
(command "_circle" "1277.938,850.7" "0.075")
(command "_circle" "1277.563,850.7" "0.15")
(command "_circle" "1277.188,850.7" "0.15")
(command "_circle" "1276.813,850.7" "0.15")
(command "_circle" "1277.938,852.7" "0.075")
(command "_circle" "1277.563,852.7" "0.075")
(command "_circle" "1277.188,852.7" "0.075")
(command "_circle" "1276.813,852.7" "0.075")
(command "_circle" "1276.438,852.7" "0.15")
(command "_circle" "1277.938,854.7" "0.075")
(command "_circle" "1277.563,854.7" "0.15")
(command "_circle" "1277.188,854.7" "0.075")
(command "_circle" "1276.813,854.7" "0.075")
(command "_circle" "1276.438,854.7" "0.15")
(command "_circle" "1277.938,856.7" "0.075")
(command "_circle" "1277.563,856.7" "0.075")
(command "_circle" "1277.188,856.7" "0.15")
(command "_circle" "1276.813,856.7" "0.075")
(command "_circle" "1276.438,856.7" "0.15")
(command "_circle" "1277.938,858.7" "0.075")
(command "_circle" "1277.563,858.7" "0.15")
(command "_circle" "1277.188,858.7" "0.15")
(command "_circle" "1276.813,858.7" "0.075")
(command "_circle" "1276.438,858.7" "0.15")
(command "_circle" "1277.938,860.7" "0.075")
(command "_circle" "1277.563,860.7" "0.075")
(command "_circle" "1277.188,860.7" "0.075")
(command "_circle" "1276.813,860.7" "0.15")
(command "_circle" "1276.438,860.7" "0.15")
(command "_circle" "1277.938,862.7" "0.075")
(command "_circle" "1277.563,862.7" "0.15")
(command "_circle" "1277.188,862.7" "0.075")
(command "_circle" "1276.813,862.7" "0.15")
(command "_circle" "1276.438,862.7" "0.15")
(command "_circle" "1277.938,864.7" "0.075")
(command "_circle" "1277.563,864.7" "0.075")
(command "_circle" "1277.188,864.7" "0.15")
(command "_circle" "1276.813,864.7" "0.15")
(command "_circle" "1276.438,864.7" "0.15")
(command "_circle" "1277.938,866.7" "0.075")
(command "_circle" "1277.563,866.7" "0.15")
(command "_circle" "1277.188,866.7" "0.15")
(command "_circle" "1276.813,866.7" "0.15")
(command "_circle" "1276.438,866.7" "0.15")
(command "_circle" "1277.938,868.7" "0.075")
(command "_circle" "1277.563,868.7" "0.075")
(command "_circle" "1277.188,868.7" "0.075")
(command "_circle" "1276.813,868.7" "0.075")
(command "_circle" "1276.438,868.7" "0.075")
(command "_circle" "1276.063,868.7" "0.15")
(command "_circle" "1277.938,870.7" "0.075")
(command "_circle" "1277.563,870.7" "0.15")
(command "_circle" "1277.188,870.7" "0.075")
(command "_circle" "1276.813,870.7" "0.075")
(command "_circle" "1276.438,870.7" "0.075")
(command "_circle" "1276.063,870.7" "0.15")
(command "_circle" "1277.938,872.7" "0.075")
(command "_circle" "1277.563,872.7" "0.075")
(command "_circle" "1277.188,872.7" "0.15")
(command "_circle" "1276.813,872.7" "0.075")
(command "_circle" "1276.438,872.7" "0.075")
(command "_circle" "1276.063,872.7" "0.15")
(command "_circle" "1277.938,874.7" "0.075")
(command "_circle" "1277.563,874.7" "0.15")
(command "_circle" "1277.188,874.7" "0.15")
(command "_circle" "1276.813,874.7" "0.075")
(command "_circle" "1276.438,874.7" "0.075")
(command "_circle" "1276.063,874.7" "0.15")
(command "_circle" "1277.938,876.7" "0.075")
(command "_circle" "1277.563,876.7" "0.075")
(command "_circle" "1277.188,876.7" "0.075")
(command "_circle" "1276.813,876.7" "0.15")
(command "_circle" "1276.438,876.7" "0.075")
(command "_circle" "1276.063,876.7" "0.15")
(command "_circle" "1277.938,878.7" "0.075")
(command "_circle" "1277.563,878.7" "0.15")
(command "_circle" "1277.188,878.7" "0.075")
(command "_circle" "1276.813,878.7" "0.15")
(command "_circle" "1276.438,878.7" "0.075")
(command "_circle" "1276.063,878.7" "0.15")
(command "_circle" "1277.938,880.7" "0.075")
(command "_circle" "1277.563,880.7" "0.075")
(command "_circle" "1277.188,880.7" "0.15")
(command "_circle" "1276.813,880.7" "0.15")
(command "_circle" "1276.438,880.7" "0.075")
(command "_circle" "1276.063,880.7" "0.15")
(command "_circle" "1277.938,882.7" "0.075")
(command "_circle" "1277.563,882.7" "0.15")
(command "_circle" "1277.188,882.7" "0.15")
(command "_circle" "1276.813,882.7" "0.15")
(command "_circle" "1276.438,882.7" "0.075")
(command "_circle" "1276.063,882.7" "0.15")
(command "_circle" "1277.938,884.7" "0.075")
(command "_circle" "1277.563,884.7" "0.075")
(command "_circle" "1277.188,884.7" "0.075")
(command "_circle" "1276.813,884.7" "0.075")
(command "_circle" "1276.438,884.7" "0.15")
(command "_circle" "1276.063,884.7" "0.15")
(command "_circle" "1277.938,886.7" "0.075")
(command "_circle" "1277.563,886.7" "0.15")
(command "_circle" "1277.188,886.7" "0.075")
(command "_circle" "1276.813,886.7" "0.075")
(command "_circle" "1276.438,886.7" "0.15")
(command "_circle" "1276.063,886.7" "0.15")
(command "_circle" "1277.938,888.7" "0.075")
(command "_circle" "1277.563,888.7" "0.075")
(command "_circle" "1277.188,888.7" "0.15")
(command "_circle" "1276.813,888.7" "0.075")
(command "_circle" "1276.438,888.7" "0.15")
(command "_circle" "1276.063,888.7" "0.15")
(command "_circle" "1277.938,890.7" "0.075")
(command "_circle" "1277.563,890.7" "0.15")
(command "_circle" "1277.188,890.7" "0.15")
(command "_circle" "1276.813,890.7" "0.075")
(command "_circle" "1276.438,890.7" "0.15")
(command "_circle" "1276.063,890.7" "0.15")
(command "_circle" "1277.938,892.7" "0.075")
(command "_circle" "1277.563,892.7" "0.075")
(command "_circle" "1277.188,892.7" "0.075")
(command "_circle" "1276.813,892.7" "0.15")
(command "_circle" "1276.438,892.7" "0.15")
(command "_circle" "1276.063,892.7" "0.15")
(command "_circle" "1277.938,894.7" "0.075")
(command "_circle" "1277.563,894.7" "0.15")
(command "_circle" "1277.188,894.7" "0.075")
(command "_circle" "1276.813,894.7" "0.15")
(command "_circle" "1276.438,894.7" "0.15")
(command "_circle" "1276.063,894.7" "0.15")
(command "_circle" "1277.938,896.7" "0.075")
(command "_circle" "1277.563,896.7" "0.075")
(command "_circle" "1277.188,896.7" "0.15")
(command "_circle" "1276.813,896.7" "0.15")
(command "_circle" "1276.438,896.7" "0.15")
(command "_circle" "1276.063,896.7" "0.15")
(command "_circle" "1277.938,898.7" "0.075")
(command "_circle" "1277.563,898.7" "0.15")
(command "_circle" "1277.188,898.7" "0.15")
(command "_circle" "1276.813,898.7" "0.15")
(command "_circle" "1276.438,898.7" "0.15")
(command "_circle" "1276.063,898.7" "0.15")
(command "_circle" "1277.938,900.7" "0.075")
(command "_circle" "1277.563,900.7" "0.075")
(command "_circle" "1277.188,900.7" "0.075")
(command "_circle" "1276.813,900.7" "0.075")
(command "_circle" "1276.438,900.7" "0.075")
(command "_circle" "1276.063,900.7" "0.075")
(command "_circle" "1275.688,900.7" "0.15")
(command "_circle" "1277.938,902.7" "0.075")
(command "_circle" "1277.563,902.7" "0.15")
(command "_circle" "1277.188,902.7" "0.075")
(command "_circle" "1276.813,902.7" "0.075")
(command "_circle" "1276.438,902.7" "0.075")
(command "_circle" "1276.063,902.7" "0.075")
(command "_circle" "1275.688,902.7" "0.15")
(command "_circle" "1277.938,904.7" "0.075")
(command "_circle" "1277.563,904.7" "0.075")
(command "_circle" "1277.188,904.7" "0.15")
(command "_circle" "1276.813,904.7" "0.075")
(command "_circle" "1276.438,904.7" "0.075")
(command "_circle" "1276.063,904.7" "0.075")
(command "_circle" "1275.688,904.7" "0.15")
(command "_circle" "1277.938,906.7" "0.075")
(command "_circle" "1277.563,906.7" "0.15")
(command "_circle" "1277.188,906.7" "0.15")
(command "_circle" "1276.813,906.7" "0.075")
(command "_circle" "1276.438,906.7" "0.075")
(command "_circle" "1276.063,906.7" "0.075")
(command "_circle" "1275.688,906.7" "0.15")
(command "_circle" "1277.938,908.7" "0.075")
(command "_circle" "1277.563,908.7" "0.075")
(command "_circle" "1277.188,908.7" "0.075")
(command "_circle" "1276.813,908.7" "0.15")
(command "_circle" "1276.438,908.7" "0.075")
(command "_circle" "1276.063,908.7" "0.075")
(command "_circle" "1275.688,908.7" "0.15")
(command "_circle" "1277.938,910.7" "0.075")
(command "_circle" "1277.563,910.7" "0.15")
(command "_circle" "1277.188,910.7" "0.075")
(command "_circle" "1276.813,910.7" "0.15")
(command "_circle" "1276.438,910.7" "0.075")
(command "_circle" "1276.063,910.7" "0.075")
(command "_circle" "1275.688,910.7" "0.15")
(command "_circle" "1277.938,912.7" "0.075")
(command "_circle" "1277.563,912.7" "0.075")
(command "_circle" "1277.188,912.7" "0.15")
(command "_circle" "1276.813,912.7" "0.15")
(command "_circle" "1276.438,912.7" "0.075")
(command "_circle" "1276.063,912.7" "0.075")
(command "_circle" "1275.688,912.7" "0.15")
(command "_circle" "1277.938,914.7" "0.075")
(command "_circle" "1277.563,914.7" "0.15")
(command "_circle" "1277.188,914.7" "0.15")
(command "_circle" "1276.813,914.7" "0.15")
(command "_circle" "1276.438,914.7" "0.075")
(command "_circle" "1276.063,914.7" "0.075")
(command "_circle" "1275.688,914.7" "0.15")
(command "_circle" "1277.938,916.7" "0.075")
(command "_circle" "1277.563,916.7" "0.075")
(command "_circle" "1277.188,916.7" "0.075")
(command "_circle" "1276.813,916.7" "0.075")
(command "_circle" "1276.438,916.7" "0.15")
(command "_circle" "1276.063,916.7" "0.075")
(command "_circle" "1275.688,916.7" "0.15")
(command "_circle" "1277.938,918.7" "0.075")
(command "_circle" "1277.563,918.7" "0.15")
(command "_circle" "1277.188,918.7" "0.075")
(command "_circle" "1276.813,918.7" "0.075")
(command "_circle" "1276.438,918.7" "0.15")
(command "_circle" "1276.063,918.7" "0.075")
(command "_circle" "1275.688,918.7" "0.15")
(command "_circle" "1277.938,920.7" "0.075")
(command "_circle" "1277.563,920.7" "0.075")
(command "_circle" "1277.188,920.7" "0.15")
(command "_circle" "1276.813,920.7" "0.075")
(command "_circle" "1276.438,920.7" "0.15")
(command "_circle" "1276.063,920.7" "0.075")
(command "_circle" "1275.688,920.7" "0.15")
(command "_circle" "1277.938,922.7" "0.075")
(command "_circle" "1277.563,922.7" "0.15")
(command "_circle" "1277.188,922.7" "0.15")
(command "_circle" "1276.813,922.7" "0.075")
(command "_circle" "1276.438,922.7" "0.15")
(command "_circle" "1276.063,922.7" "0.075")
(command "_circle" "1275.688,922.7" "0.15")
(command "_circle" "1277.938,924.7" "0.075")
(command "_circle" "1277.563,924.7" "0.075")
(command "_circle" "1277.188,924.7" "0.075")
(command "_circle" "1276.813,924.7" "0.15")
(command "_circle" "1276.438,924.7" "0.15")
(command "_circle" "1276.063,924.7" "0.075")
(command "_circle" "1275.688,924.7" "0.15")
(command "_circle" "1277.938,926.7" "0.075")
(command "_circle" "1277.563,926.7" "0.15")
(command "_circle" "1277.188,926.7" "0.075")
(command "_circle" "1276.813,926.7" "0.15")
(command "_circle" "1276.438,926.7" "0.15")
(command "_circle" "1276.063,926.7" "0.075")
(command "_circle" "1275.688,926.7" "0.15")
(command "_circle" "1277.938,928.7" "0.075")
(command "_circle" "1277.563,928.7" "0.075")
(command "_circle" "1277.188,928.7" "0.15")
(command "_circle" "1276.813,928.7" "0.15")
(command "_circle" "1276.438,928.7" "0.15")
(command "_circle" "1276.063,928.7" "0.075")
(command "_circle" "1275.688,928.7" "0.15")
(command "_circle" "1277.938,930.7" "0.075")
(command "_circle" "1277.563,930.7" "0.15")
(command "_circle" "1277.188,930.7" "0.15")
(command "_circle" "1276.813,930.7" "0.15")
(command "_circle" "1276.438,930.7" "0.15")
(command "_circle" "1276.063,930.7" "0.075")
(command "_circle" "1275.688,930.7" "0.15")
(command "_circle" "1277.938,932.7" "0.075")
(command "_circle" "1277.563,932.7" "0.075")
(command "_circle" "1277.188,932.7" "0.075")
(command "_circle" "1276.813,932.7" "0.075")
(command "_circle" "1276.438,932.7" "0.075")
(command "_circle" "1276.063,932.7" "0.15")
(command "_circle" "1275.688,932.7" "0.15")
(command "_circle" "1277.938,934.7" "0.075")
(command "_circle" "1277.563,934.7" "0.15")
(command "_circle" "1277.188,934.7" "0.075")
(command "_circle" "1276.813,934.7" "0.075")
(command "_circle" "1276.438,934.7" "0.075")
(command "_circle" "1276.063,934.7" "0.15")
(command "_circle" "1275.688,934.7" "0.15")
(command "_circle" "1277.938,936.7" "0.075")
(command "_circle" "1277.563,936.7" "0.075")
(command "_circle" "1277.188,936.7" "0.15")
(command "_circle" "1276.813,936.7" "0.075")
(command "_circle" "1276.438,936.7" "0.075")
(command "_circle" "1276.063,936.7" "0.15")
(command "_circle" "1275.688,936.7" "0.15")
(command "_circle" "1277.938,938.7" "0.075")
(command "_circle" "1277.563,938.7" "0.15")
(command "_circle" "1277.188,938.7" "0.15")
(command "_circle" "1276.813,938.7" "0.075")
(command "_circle" "1276.438,938.7" "0.075")
(command "_circle" "1276.063,938.7" "0.15")
(command "_circle" "1275.688,938.7" "0.15")
(command "_circle" "1277.938,940.7" "0.075")
(command "_circle" "1277.563,940.7" "0.075")
(command "_circle" "1277.188,940.7" "0.075")
(command "_circle" "1276.813,940.7" "0.15")
(command "_circle" "1276.438,940.7" "0.075")
(command "_circle" "1276.063,940.7" "0.15")
(command "_circle" "1275.688,940.7" "0.15")
(command "_circle" "1277.938,942.7" "0.075")
(command "_circle" "1277.563,942.7" "0.15")
(command "_circle" "1277.188,942.7" "0.075")
(command "_circle" "1276.813,942.7" "0.15")
(command "_circle" "1276.438,942.7" "0.075")
(command "_circle" "1276.063,942.7" "0.15")
(command "_circle" "1275.688,942.7" "0.15")
(command "_circle" "1277.938,944.7" "0.075")
(command "_circle" "1277.563,944.7" "0.075")
(command "_circle" "1277.188,944.7" "0.15")
(command "_circle" "1276.813,944.7" "0.15")
(command "_circle" "1276.438,944.7" "0.075")
(command "_circle" "1276.063,944.7" "0.15")
(command "_circle" "1275.688,944.7" "0.15")
(command "_circle" "1277.938,946.7" "0.075")
(command "_circle" "1277.563,946.7" "0.15")
(command "_circle" "1277.188,946.7" "0.15")
(command "_circle" "1276.813,946.7" "0.15")
(command "_circle" "1276.438,946.7" "0.075")
(command "_circle" "1276.063,946.7" "0.15")
(command "_circle" "1275.688,946.7" "0.15")
(command "_circle" "1277.938,948.7" "0.075")
(command "_circle" "1277.563,948.7" "0.075")
(command "_circle" "1277.188,948.7" "0.075")
(command "_circle" "1276.813,948.7" "0.075")
(command "_circle" "1276.438,948.7" "0.15")
(command "_circle" "1276.063,948.7" "0.15")
(command "_circle" "1275.688,948.7" "0.15")
(command "_circle" "1277.938,950.7" "0.075")
(command "_circle" "1277.563,950.7" "0.15")
(command "_circle" "1277.188,950.7" "0.075")
(command "_circle" "1276.813,950.7" "0.075")
(command "_circle" "1276.438,950.7" "0.15")
(command "_circle" "1276.063,950.7" "0.15")
(command "_circle" "1275.688,950.7" "0.15")
(command "_circle" "1277.938,952.7" "0.075")
(command "_circle" "1277.563,952.7" "0.075")
(command "_circle" "1277.188,952.7" "0.15")
(command "_circle" "1276.813,952.7" "0.075")
(command "_circle" "1276.438,952.7" "0.15")
(command "_circle" "1276.063,952.7" "0.15")
(command "_circle" "1275.688,952.7" "0.15")
(command "_circle" "1277.938,954.7" "0.075")
(command "_circle" "1277.563,954.7" "0.15")
(command "_circle" "1277.188,954.7" "0.15")
(command "_circle" "1276.813,954.7" "0.075")
(command "_circle" "1276.438,954.7" "0.15")
(command "_circle" "1276.063,954.7" "0.15")
(command "_circle" "1275.688,954.7" "0.15")
(command "_circle" "1277.938,956.7" "0.075")
(command "_circle" "1277.563,956.7" "0.075")
(command "_circle" "1277.188,956.7" "0.075")
(command "_circle" "1276.813,956.7" "0.15")
(command "_circle" "1276.438,956.7" "0.15")
(command "_circle" "1276.063,956.7" "0.15")
(command "_circle" "1275.688,956.7" "0.15")
(command "_circle" "1277.938,958.7" "0.075")
(command "_circle" "1277.563,958.7" "0.15")
(command "_circle" "1277.188,958.7" "0.075")
(command "_circle" "1276.813,958.7" "0.15")
(command "_circle" "1276.438,958.7" "0.15")
(command "_circle" "1276.063,958.7" "0.15")
(command "_circle" "1275.688,958.7" "0.15")
(command "_circle" "1277.938,960.7" "0.075")
(command "_circle" "1277.563,960.7" "0.075")
(command "_circle" "1277.188,960.7" "0.15")
(command "_circle" "1276.813,960.7" "0.15")
(command "_circle" "1276.438,960.7" "0.15")
(command "_circle" "1276.063,960.7" "0.15")
(command "_circle" "1275.688,960.7" "0.15")
(command "_circle" "1277.938,962.7" "0.075")
(command "_circle" "1277.563,962.7" "0.15")
(command "_circle" "1277.188,962.7" "0.15")
(command "_circle" "1276.813,962.7" "0.15")
(command "_circle" "1276.438,962.7" "0.15")
(command "_circle" "1276.063,962.7" "0.15")
(command "_circle" "1275.688,962.7" "0.15")
(command "_layer" "set" "nitride" "")
(command "_layer" "set" "text" "")
(command-s "_text" "1266.888,963.3" "2" "-90" "a = 370 nm" )
(sssetfirst nil (ssget "_L"))
(if (not (numberp (vl-string-search "Mac" (getvar "platform")))) (c:txtexp))
(command "_layer" "set" "nitride" "")
(command "_layer" "set" "text" "")
(command-s "_text" "1263.888,963.3" "2" "-90" "gap = 250 nm" )
(sssetfirst nil (ssget "_L"))
(if (not (numberp (vl-string-search "Mac" (getvar "platform")))) (c:txtexp))
(command "_layer" "set" "nitride" "")
(command "_layer" "set" "text" "")
(command-s "_text" "1260.888,963.3" "2" "-90" "amplitude = 142 nm" )
(sssetfirst nil (ssget "_L"))
(if (not (numberp (vl-string-search "Mac" (getvar "platform")))) (c:txtexp))
(command "_layer" "set" "nitride" "")
(command "_layer" "set" "text" "")
(command-s "_text" "1257.888,963.3" "2" "-90" "start width = 280 nm" )
(sssetfirst nil (ssget "_L"))
(if (not (numberp (vl-string-search "Mac" (getvar "platform")))) (c:txtexp))
(command "_layer" "set" "nitride" "")
(command "_layer" "set" "text" "")
(command-s "_text" "1254.888,963.3" "2" "-90" "width = 289 nm" )
(sssetfirst nil (ssget "_L"))
(if (not (numberp (vl-string-search "Mac" (getvar "platform")))) (c:txtexp))
(command "_layer" "set" "nitride" "")
(command "_layer" "set" "text" "")
(command-s "_text" "1251.888,963.3" "2" "-90" "taper: 15" )
(sssetfirst nil (ssget "_L"))
(if (not (numberp (vl-string-search "Mac" (getvar "platform")))) (c:txtexp))
(command "_layer" "set" "nitride" "")
(command "_layer" "set" "text" "")
(command-s "_text" "1248.888,963.3" "2" "-90" "nominal: 150" )
(sssetfirst nil (ssget "_L"))
(if (not (numberp (vl-string-search "Mac" (getvar "platform")))) (c:txtexp))
(command "_layer" "set" "nitride" "")
(command "_layer" "set" "indicators" "")
(setq coords (list 
(list 1200.415 940) 
(list 1200.415 920) 
(list 1180.415 900) 
(list 1200.415 880) 
(list 1200.415 860) 
(list 1200.415 900) 
(list 1200.415 887.0711) 
(list 1187.4861 900) 
(list 1200.415 912.9289) 
(list 1200.415 900)))
(apply 'command (append '("pline") coords '("c")))
(command "._fillet" "radius" "1" "._fillet" "P" (entlast))
(setq coords (list 
(list 1359.585 940) 
(list 1359.585 920) 
(list 1379.585 900) 
(list 1359.585 880) 
(list 1359.585 860) 
(list 1359.585 900) 
(list 1359.585 887.0711) 
(list 1372.5139 900) 
(list 1359.585 912.9289) 
(list 1359.585 900)))
(apply 'command (append '("pline") coords '("c")))
(command "._fillet" "radius" "1" "._fillet" "P" (entlast))
(command "_layer" "set" "holes" "")
(command "_circle" "1198.0629,914.1124" "0.5")
(command "_circle" "1195.7109,911.7603" "0.5")
(command "_circle" "1193.3588,909.4083" "0.5")
(command "_circle" "1191.0067,907.0562" "0.5")
(command "_circle" "1188.6547,904.7041" "0.5")
(command "_circle" "1186.3026,902.3521" "0.5")
(command "_circle" "1183.9505,900" "0.5")
(command "_circle" "1186.3026,897.6479" "0.5")
(command "_circle" "1188.6547,895.2959" "0.5")
(command "_circle" "1191.0067,892.9438" "0.5")
(command "_circle" "1193.3588,890.5917" "0.5")
(command "_circle" "1195.7109,888.2397" "0.5")
(command "_circle" "1198.0629,885.8876" "0.5")
(command "_circle" "1361.9371,914.1124" "0.5")
(command "_circle" "1364.2891,911.7603" "0.5")
(command "_circle" "1366.6412,909.4083" "0.5")
(command "_circle" "1368.9933,907.0562" "0.5")
(command "_circle" "1371.3453,904.7041" "0.5")
(command "_circle" "1373.6974,902.3521" "0.5")
(command "_circle" "1376.0495,900" "0.5")
(command "_circle" "1373.6974,897.6479" "0.5")
(command "_circle" "1371.3453,895.2959" "0.5")
(command "_circle" "1368.9933,892.9438" "0.5")
(command "_circle" "1366.6412,890.5917" "0.5")
(command "_circle" "1364.2891,888.2397" "0.5")
(command "_circle" "1361.9371,885.8876" "0.5")
(command "_layer" "set" "nitride" "")
(command "_block" "blkcoupler4" "1280,900" coupler4 "")
(command "_insert" "blkcoupler4" "1280,900" "1" "1" "0")
(command "_insert" "blkcoupler4" "1280,900" "1" "1" "180")
(command "_block" "blksinglenanobeam4" "1280,900" singlenanobeam4 "")
(command "_insert" "blksinglenanobeam4" "1280,900" "1" "1" "0")
(command "_insert" "blksinglenanobeam4" "1280,900" "1" "1" "180")
(command "_block" "blkanglednodearray4" "1280,900" anglednodearray4 "")
(command "_insert" "blkanglednodearray4" "1280,900" "1" "1" "0")
(command "_insert" "blkanglednodearray4" "1280,900" "1" "1" "180")
(command "_block" "blkcooledsinglenanobeam4" "1280,900" cooledsinglenanobeam4 "")
(command "_insert" "blkcooledsinglenanobeam4" "1280,900" "1" "1" "0")
(command "_insert" "blkcooledsinglenanobeam4" "1280,900" "1" "1" "180")
(command "_block" "blkyjunction4" "1280,900" yjunction4 "")
(command "_insert" "blkyjunction4" "1280,900" "1" "1" "0")
(command "_insert" "blkyjunction4" "1280,900" "1" "1" "180")
; DRAWING BULGING VEE GROOVE
(command "_layer" "set" "vgroove" "")
(setq coords (list 
(list 1205.415 -605) 
(list 1205.415 0) 
(list 1205.415 0) 
(list 1205.415 1800) 
(list 1205.415 1800) 
(list 1205.415 2405) 
(list 1354.585 2405) 
(list 1354.585 1800) 
(list 1354.585 1800) 
(list 1354.585 0) 
(list 1354.585 0) 
(list 1354.585 -605)))
(apply 'command (append '("pline") coords '("c")))
(command "._fillet" "radius" "0" "._fillet" "P" (entlast))
(command "_layer" "set" "window" "")
(command "_rectangle" "1205.415,-1935" "1354.585,-600")
(command "_rectangle" "1205.415,2400" "1354.585,5300")
(command "_layer" "set" "grid" "")
(command "_rectangle" "1206.415,-1934" "1229.9433,-1909.2133")
(command "_array" "last" "" "R" "75" "3" "25.7867" "24.5283")
(command "_rectangle" "1281,-1934" "1304.5283,-1909.2133")
(command "_array" "last" "" "R" "75" "3" "25.7867" "24.5283")
(command "_rectangle" "1206.415,1" "1229.9433,25.7")
(command "_array" "last" "" "R" "70" "3" "25.7" "24.5283")
(command "_rectangle" "1281,1" "1304.5283,25.7")
(command "_array" "last" "" "R" "70" "3" "25.7" "24.5283")
(command "_rectangle" "1206.415,1801" "1229.9433,1825.9185")
(command "_array" "last" "" "R" "135" "3" "25.9185" "24.5283")
(command "_rectangle" "1281,1801" "1304.5283,1825.9185")
(command "_array" "last" "" "R" "135" "3" "25.9185" "24.5283")
(command "_layer" "set" "vgrooveFDA" "")
(command "_rectangle" "1354.585,-2233" "1205.415,-1933")
(command "_layer" "set" "nitride" "")
(command "_layer" "set" "holes" "")
(command "_circle" "1357.085,331.5" "0.5")
(command "_array" "last" "" "R" "379" "1" "3" "2.5")
(command "_circle" "1202.915,331.5" "0.5")
(command "_array" "last" "" "R" "379" "1" "3" "-2.5")
(command "_layer" "set" "nitride" "")
(command "_layer" "set" "window" "")
(command "_layer" "set" "window" "")
(command "_rectangle" "1359.585,0" "1520.415,1800")
(command "._fillet" "radius" "20" "._fillet" "P" (entlast))
(command "_layer" "set" "grid" "")
(command "_rectangle" "1360.585,1" "1382.4179,25.7")
(command "_array" "last" "" "R" "70" "7" "25.7" "22.8329")
(command "_layer" "set" "nitride" "")
; DRAWING REGION LAYER
(command "_layer" "set" "regionLayer4" "")
(command "_rectangle" "1200,-460" "1360,2260")
(command "_layer" "set" "nitride" "")
(setq coupler4 nil)
(setq singlenanobeam4 nil)
(setq anglednodearray4 nil)
(setq cooledsinglenanobeam4 nil)
(setq yjunction4 nil)
; DEVICE #5
(command "_layer" "set" "window" "")
(command "_circle" "1512.915,-415" "5")
(command "_circle" "1512.915,-402.5" "5")
(command "_circle" "1512.915,-390" "5")
(command "_circle" "1512.915,-377.5" "5")
(command "_circle" "1500.415,-415" "5")
(command "_layer" "set" "nitride" "")
(setq currobj nil)
(setq currobj (ssadd))
; DRAWING COUPLER
(setq coords (list 
(list 1600.0615 -415) 
(list 1600.0615 -413) 
(list 1673.585 -413) 
(list 1673.585 -413) 
(list 1673.9677 -413.0761) 
(list 1674.2921 -413.2929) 
(list 1674.5089 -413.6173) 
(list 1674.585 -414) 
(list 1674.585 -411.8) 
(list 1674.585 -411.8) 
(list 1674.5089 -412.1827) 
(list 1674.2921 -412.5071) 
(list 1673.9677 -412.7239) 
(list 1673.585 -412.8) 
(list 1600.0615 -412.8) 
(list 1600.0615 -410.8) 
(list 1599.9385 -410.8) 
(list 1599.9385 -412.8) 
(list 1526.415 -412.8) 
(list 1526.0323 -412.7239) 
(list 1525.7079 -412.5071) 
(list 1525.4911 -412.1827) 
(list 1525.415 -411.8) 
(list 1525.415 -411.8) 
(list 1525.415 -414) 
(list 1525.4911 -413.6173) 
(list 1525.7079 -413.2929) 
(list 1526.0323 -413.0761) 
(list 1526.415 -413) 
(list 1526.415 -413) 
(list 1599.9385 -413) 
(list 1599.9385 -415)))
(apply 'command (append '("pline") coords '("c")))
(setq currobj (ssadd (entlast) currobj))
(command "._fillet" "radius" "0.3" "._fillet" "P" (entlast))
(command "_layer" "set" "holes" "")
(command "_circle" "1600,-412.9" "0.113")
(setq currobj (ssadd (entlast) currobj))
(command "_layer" "set" "nitride" "")
(command "_layer" "set" "text" "")
(command "_circle" "1599.2,-415" "0.075")
(command "_circle" "1599.2,-414.7" "0.075")
(command "_circle" "1599.2,-414.4" "0.075")
(command "_circle" "1598.9,-415" "0.075")
(command "_circle" "1598.9,-414.7" "0.075")
(command "_circle" "1598.9,-414.4" "0.075")
(command "_circle" "1598.6,-415" "0.075")
(command "_circle" "1598.6,-414.7" "0.075")
(command "_circle" "1598.6,-414.4" "0.075")
(command "_layer" "set" "nitride" "")
(command "_layer" "set" "prebias" "")
(command "_rectangle" "1525.415,-414" "1674.585,-411.8")
(setq currobj (ssadd (entlast) currobj))
(command "_rectangle" "1599.9385,-415" "1600.0615,-410.8")
(setq currobj (ssadd (entlast) currobj))
(command "_layer" "set" "nitride" "")
(setq coupler5 currobj)
(setq currobj nil)
(setq currobj (ssadd))
; DRAWING SINGLE NANOBEAM
(setq coords (list 
(list 1600.0615 -410.8) 
(list 1600.0615 -409.1417) 
(list 1600.0615 -407.4833) 
(list 1600.0615 -405.825) 
(list 1600.0615 -404.1667) 
(list 1600.0615 -402.5083) 
(list 1600.0615 -400.85) 
(list 1600.0615 -399.1917) 
(list 1600.0615 -397.5333) 
(list 1600.0616 -395.875) 
(list 1600.0616 -394.2167) 
(list 1600.0616 -392.5583) 
(list 1600.0616 -390.9) 
(list 1600.0617 -389.2417) 
(list 1600.0617 -387.5833) 
(list 1600.0617 -385.925) 
(list 1600.0618 -384.2667) 
(list 1600.0619 -382.6083) 
(list 1600.0619 -380.95) 
(list 1600.062 -379.2917) 
(list 1600.0621 -377.6333) 
(list 1600.0622 -375.975) 
(list 1600.0623 -374.3167) 
(list 1600.0624 -372.6583) 
(list 1600.0625 -371) 
(list 1600.0626 -369.3417) 
(list 1600.0628 -367.6833) 
(list 1600.0629 -366.025) 
(list 1600.0631 -364.3667) 
(list 1600.0632 -362.7083) 
(list 1600.0634 -361.05) 
(list 1600.0636 -359.3917) 
(list 1600.0638 -357.7333) 
(list 1600.0641 -356.075) 
(list 1600.0643 -354.4167) 
(list 1600.0646 -352.7583) 
(list 1600.0648 -351.1) 
(list 1600.0651 -349.4417) 
(list 1600.0654 -347.7833) 
(list 1600.0657 -346.125) 
(list 1600.0661 -344.4667) 
(list 1600.0664 -342.8083) 
(list 1600.0668 -341.15) 
(list 1600.0672 -339.4917) 
(list 1600.0676 -337.8333) 
(list 1600.068 -336.175) 
(list 1600.0685 -334.5167) 
(list 1600.0689 -332.8583) 
(list 1600.0694 -331.2) 
(list 1600.0699 -329.5417) 
(list 1600.0704 -327.8833) 
(list 1600.071 -326.225) 
(list 1600.0715 -324.5667) 
(list 1600.0721 -322.9083) 
(list 1600.0728 -321.25) 
(list 1600.0734 -319.5917) 
(list 1600.0741 -317.9333) 
(list 1600.0747 -316.275) 
(list 1600.0754 -314.6167) 
(list 1600.0762 -312.9583) 
(list 1600.0769 -311.3) 
(list 1600.0777 -309.6417) 
(list 1600.0785 -307.9833) 
(list 1600.0794 -306.325) 
(list 1600.0802 -304.6667) 
(list 1600.0811 -303.0083) 
(list 1600.082 -301.35) 
(list 1600.083 -299.6917) 
(list 1600.084 -298.0333) 
(list 1600.085 -296.375) 
(list 1600.086 -294.7167) 
(list 1600.0871 -293.0583) 
(list 1600.0882 -291.4) 
(list 1600.0893 -289.7417) 
(list 1600.0905 -288.0833) 
(list 1600.0917 -286.425) 
(list 1600.0929 -284.7667) 
(list 1600.0941 -283.1083) 
(list 1600.0954 -281.45) 
(list 1600.0967 -279.7917) 
(list 1600.0981 -278.1333) 
(list 1600.0995 -276.475) 
(list 1600.1009 -274.8167) 
(list 1600.1024 -273.1583) 
(list 1600.1039 -271.5) 
(list 1600.1054 -269.8417) 
(list 1600.107 -268.1833) 
(list 1600.1086 -266.525) 
(list 1600.1102 -264.8667) 
(list 1600.1119 -263.2083) 
(list 1600.1136 -261.55) 
(list 1600.1154 -259.8917) 
(list 1600.1172 -258.2333) 
(list 1600.119 -256.575) 
(list 1600.1209 -254.9167) 
(list 1600.1228 -253.2583) 
(list 1600.1247 -251.6) 
(list 1600.1267 -249.9417) 
(list 1600.1288 -248.2833) 
(list 1600.1308 -246.625) 
(list 1600.133 -244.9667) 
(list 1600.1351 -243.3083) 
(list 1600.1373 -241.65) 
(list 1600.1396 -239.9917) 
(list 1600.1419 -238.3333) 
(list 1600.1442 -236.675) 
(list 1600.1466 -235.0167) 
(list 1600.1491 -233.3583) 
(list 1600.1515 -231.7) 
(list 1600.1541 -230.0417) 
(list 1600.1566 -228.3833) 
(list 1600.1592 -226.725) 
(list 1600.1619 -225.0667) 
(list 1600.1646 -223.4083) 
(list 1600.1674 -221.75) 
(list 1600.1702 -220.0917) 
(list 1600.1731 -218.4333) 
(list 1600.176 -216.775) 
(list 1600.1789 -215.1167) 
(list 1600.1819 -213.4583) 
(list 1600.185 -211.8) 
(list 1599.815 -211.8) 
(list 1599.8181 -213.4583) 
(list 1599.8211 -215.1167) 
(list 1599.824 -216.775) 
(list 1599.8269 -218.4333) 
(list 1599.8298 -220.0917) 
(list 1599.8326 -221.75) 
(list 1599.8354 -223.4083) 
(list 1599.8381 -225.0667) 
(list 1599.8408 -226.725) 
(list 1599.8434 -228.3833) 
(list 1599.8459 -230.0417) 
(list 1599.8485 -231.7) 
(list 1599.8509 -233.3583) 
(list 1599.8534 -235.0167) 
(list 1599.8558 -236.675) 
(list 1599.8581 -238.3333) 
(list 1599.8604 -239.9917) 
(list 1599.8627 -241.65) 
(list 1599.8649 -243.3083) 
(list 1599.867 -244.9667) 
(list 1599.8692 -246.625) 
(list 1599.8712 -248.2833) 
(list 1599.8733 -249.9417) 
(list 1599.8753 -251.6) 
(list 1599.8772 -253.2583) 
(list 1599.8791 -254.9167) 
(list 1599.881 -256.575) 
(list 1599.8828 -258.2333) 
(list 1599.8846 -259.8917) 
(list 1599.8864 -261.55) 
(list 1599.8881 -263.2083) 
(list 1599.8898 -264.8667) 
(list 1599.8914 -266.525) 
(list 1599.893 -268.1833) 
(list 1599.8946 -269.8417) 
(list 1599.8961 -271.5) 
(list 1599.8976 -273.1583) 
(list 1599.8991 -274.8167) 
(list 1599.9005 -276.475) 
(list 1599.9019 -278.1333) 
(list 1599.9033 -279.7917) 
(list 1599.9046 -281.45) 
(list 1599.9059 -283.1083) 
(list 1599.9071 -284.7667) 
(list 1599.9083 -286.425) 
(list 1599.9095 -288.0833) 
(list 1599.9107 -289.7417) 
(list 1599.9118 -291.4) 
(list 1599.9129 -293.0583) 
(list 1599.914 -294.7167) 
(list 1599.915 -296.375) 
(list 1599.916 -298.0333) 
(list 1599.917 -299.6917) 
(list 1599.918 -301.35) 
(list 1599.9189 -303.0083) 
(list 1599.9198 -304.6667) 
(list 1599.9206 -306.325) 
(list 1599.9215 -307.9833) 
(list 1599.9223 -309.6417) 
(list 1599.9231 -311.3) 
(list 1599.9238 -312.9583) 
(list 1599.9246 -314.6167) 
(list 1599.9253 -316.275) 
(list 1599.9259 -317.9333) 
(list 1599.9266 -319.5917) 
(list 1599.9272 -321.25) 
(list 1599.9279 -322.9083) 
(list 1599.9285 -324.5667) 
(list 1599.929 -326.225) 
(list 1599.9296 -327.8833) 
(list 1599.9301 -329.5417) 
(list 1599.9306 -331.2) 
(list 1599.9311 -332.8583) 
(list 1599.9315 -334.5167) 
(list 1599.932 -336.175) 
(list 1599.9324 -337.8333) 
(list 1599.9328 -339.4917) 
(list 1599.9332 -341.15) 
(list 1599.9336 -342.8083) 
(list 1599.9339 -344.4667) 
(list 1599.9343 -346.125) 
(list 1599.9346 -347.7833) 
(list 1599.9349 -349.4417) 
(list 1599.9352 -351.1) 
(list 1599.9354 -352.7583) 
(list 1599.9357 -354.4167) 
(list 1599.9359 -356.075) 
(list 1599.9362 -357.7333) 
(list 1599.9364 -359.3917) 
(list 1599.9366 -361.05) 
(list 1599.9368 -362.7083) 
(list 1599.9369 -364.3667) 
(list 1599.9371 -366.025) 
(list 1599.9372 -367.6833) 
(list 1599.9374 -369.3417) 
(list 1599.9375 -371) 
(list 1599.9376 -372.6583) 
(list 1599.9377 -374.3167) 
(list 1599.9378 -375.975) 
(list 1599.9379 -377.6333) 
(list 1599.938 -379.2917) 
(list 1599.9381 -380.95) 
(list 1599.9381 -382.6083) 
(list 1599.9382 -384.2667) 
(list 1599.9383 -385.925) 
(list 1599.9383 -387.5833) 
(list 1599.9383 -389.2417) 
(list 1599.9384 -390.9) 
(list 1599.9384 -392.5583) 
(list 1599.9384 -394.2167) 
(list 1599.9384 -395.875) 
(list 1599.9385 -397.5333) 
(list 1599.9385 -399.1917) 
(list 1599.9385 -400.85) 
(list 1599.9385 -402.5083) 
(list 1599.9385 -404.1667) 
(list 1599.9385 -405.825) 
(list 1599.9385 -407.4833) 
(list 1599.9385 -409.1417) 
(list 1599.9385 -410.8)))
(apply 'command (append '("pline") coords '("c")))
(setq currobj (ssadd (entlast) currobj))
(command "_layer" "set" "prebias" "")
(command "_rectangle" "1599.815,-410.8" "1600.185,-211.8")
(setq currobj (ssadd (entlast) currobj))
(command "_layer" "set" "nitride" "")
(setq singlenanobeam5 currobj)
(setq currobj nil)
(setq currobj (ssadd))
; DRAWING NODE ARRAY
(setq coords (list 
(list 1600.185 -211.8) 
(list 1600.5625 -201.8) 
(list 1600.5625 -201.8) 
(list 1600.5625 -200.8) 
(list 1674.585 -212.6864) 
(list 1674.585 -207.7434) 
(list 1600.5625 -197.357) 
(list 1600.5625 -196.357) 
(list 1600.5625 -196.357) 
(list 1600.2625 -186.357) 
(list 1599.7375 -186.357) 
(list 1599.4375 -196.357) 
(list 1599.4375 -196.357) 
(list 1599.4375 -197.357) 
(list 1525.415 -207.7434) 
(list 1525.415 -212.6864) 
(list 1599.4375 -200.8) 
(list 1599.4375 -201.8) 
(list 1599.4375 -201.8) 
(list 1599.815 -211.8)))
(apply 'command (append '("pline") coords '("c")))
(setq currobj (ssadd (entlast) currobj))
(command "_layer" "set" "prebias" "")
(setq coords (list 
(list 1599.4375 -212.6864) 
(list 1599.4375 -200.8) 
(list 1525.415 -212.6864) 
(list 1525.415 -207.7434) 
(list 1599.4375 -197.357) 
(list 1599.4375 -186.357) 
(list 1600.5625 -186.357) 
(list 1600.5625 -197.357) 
(list 1674.585 -207.7434) 
(list 1674.585 -212.6864) 
(list 1600.5625 -200.8) 
(list 1600.5625 -212.6864)))
(apply 'command (append '("pline") coords '("c")))
(setq currobj (ssadd (entlast) currobj))
(command "_layer" "set" "nitride" "")
(command "_layer" "set" "fda1" "")
(setq coords (list 
(list 1600.5625 -200.657) 
(list 1674.585 -212.5434) 
(list 1674.585 -212.3664) 
(list 1600.5625 -200.58)))
(apply 'command (append '("pline") coords '("c")))
(setq currobj (ssadd (entlast) currobj))
(setq coords (list 
(list 1600.5625 -200.437) 
(list 1674.585 -212.2234) 
(list 1674.585 -212.0464) 
(list 1600.5625 -200.36)))
(apply 'command (append '("pline") coords '("c")))
(setq currobj (ssadd (entlast) currobj))
(setq coords (list 
(list 1600.5625 -200.217) 
(list 1674.585 -211.9034) 
(list 1674.585 -211.7264) 
(list 1600.5625 -200.14)))
(apply 'command (append '("pline") coords '("c")))
(setq currobj (ssadd (entlast) currobj))
(setq coords (list 
(list 1600.5625 -199.997) 
(list 1674.585 -211.5834) 
(list 1674.585 -211.4064) 
(list 1600.5625 -199.92)))
(apply 'command (append '("pline") coords '("c")))
(setq currobj (ssadd (entlast) currobj))
(setq coords (list 
(list 1600.5625 -199.777) 
(list 1674.585 -211.2634) 
(list 1674.585 -211.0864) 
(list 1600.5625 -199.7)))
(apply 'command (append '("pline") coords '("c")))
(setq currobj (ssadd (entlast) currobj))
(setq coords (list 
(list 1600.5625 -199.557) 
(list 1674.585 -210.9434) 
(list 1674.585 -210.7664) 
(list 1600.5625 -199.48)))
(apply 'command (append '("pline") coords '("c")))
(setq currobj (ssadd (entlast) currobj))
(setq coords (list 
(list 1600.5625 -199.337) 
(list 1674.585 -210.6234) 
(list 1674.585 -210.4464) 
(list 1600.5625 -199.26)))
(apply 'command (append '("pline") coords '("c")))
(setq currobj (ssadd (entlast) currobj))
(setq coords (list 
(list 1600.5625 -199.117) 
(list 1674.585 -210.3034) 
(list 1674.585 -210.1264) 
(list 1600.5625 -199.04)))
(apply 'command (append '("pline") coords '("c")))
(setq currobj (ssadd (entlast) currobj))
(setq coords (list 
(list 1600.5625 -198.897) 
(list 1674.585 -209.9834) 
(list 1674.585 -209.8064) 
(list 1600.5625 -198.82)))
(apply 'command (append '("pline") coords '("c")))
(setq currobj (ssadd (entlast) currobj))
(setq coords (list 
(list 1600.5625 -198.677) 
(list 1674.585 -209.6634) 
(list 1674.585 -209.4864) 
(list 1600.5625 -198.6)))
(apply 'command (append '("pline") coords '("c")))
(setq currobj (ssadd (entlast) currobj))
(setq coords (list 
(list 1600.5625 -198.457) 
(list 1674.585 -209.3434) 
(list 1674.585 -209.1664) 
(list 1600.5625 -198.38)))
(apply 'command (append '("pline") coords '("c")))
(setq currobj (ssadd (entlast) currobj))
(setq coords (list 
(list 1600.5625 -198.237) 
(list 1674.585 -209.0234) 
(list 1674.585 -208.8464) 
(list 1600.5625 -198.16)))
(apply 'command (append '("pline") coords '("c")))
(setq currobj (ssadd (entlast) currobj))
(setq coords (list 
(list 1600.5625 -198.017) 
(list 1674.585 -208.7034) 
(list 1674.585 -208.5264) 
(list 1600.5625 -197.94)))
(apply 'command (append '("pline") coords '("c")))
(setq currobj (ssadd (entlast) currobj))
(setq coords (list 
(list 1600.5625 -197.797) 
(list 1674.585 -208.3834) 
(list 1674.585 -208.2064) 
(list 1600.5625 -197.72)))
(apply 'command (append '("pline") coords '("c")))
(setq currobj (ssadd (entlast) currobj))
(setq coords (list 
(list 1600.5625 -197.577) 
(list 1674.585 -208.0634) 
(list 1674.585 -207.8864) 
(list 1600.5625 -197.5)))
(apply 'command (append '("pline") coords '("c")))
(setq currobj (ssadd (entlast) currobj))
(setq coords (list 
(list 1599.4375 -197.5) 
(list 1525.415 -207.8864) 
(list 1525.415 -208.0634) 
(list 1599.4375 -197.577)))
(apply 'command (append '("pline") coords '("c")))
(setq currobj (ssadd (entlast) currobj))
(setq coords (list 
(list 1599.4375 -197.72) 
(list 1525.415 -208.2064) 
(list 1525.415 -208.3834) 
(list 1599.4375 -197.797)))
(apply 'command (append '("pline") coords '("c")))
(setq currobj (ssadd (entlast) currobj))
(setq coords (list 
(list 1599.4375 -197.94) 
(list 1525.415 -208.5264) 
(list 1525.415 -208.7034) 
(list 1599.4375 -198.017)))
(apply 'command (append '("pline") coords '("c")))
(setq currobj (ssadd (entlast) currobj))
(setq coords (list 
(list 1599.4375 -198.16) 
(list 1525.415 -208.8464) 
(list 1525.415 -209.0234) 
(list 1599.4375 -198.237)))
(apply 'command (append '("pline") coords '("c")))
(setq currobj (ssadd (entlast) currobj))
(setq coords (list 
(list 1599.4375 -198.38) 
(list 1525.415 -209.1664) 
(list 1525.415 -209.3434) 
(list 1599.4375 -198.457)))
(apply 'command (append '("pline") coords '("c")))
(setq currobj (ssadd (entlast) currobj))
(setq coords (list 
(list 1599.4375 -198.6) 
(list 1525.415 -209.4864) 
(list 1525.415 -209.6634) 
(list 1599.4375 -198.677)))
(apply 'command (append '("pline") coords '("c")))
(setq currobj (ssadd (entlast) currobj))
(setq coords (list 
(list 1599.4375 -198.82) 
(list 1525.415 -209.8064) 
(list 1525.415 -209.9834) 
(list 1599.4375 -198.897)))
(apply 'command (append '("pline") coords '("c")))
(setq currobj (ssadd (entlast) currobj))
(setq coords (list 
(list 1599.4375 -199.04) 
(list 1525.415 -210.1264) 
(list 1525.415 -210.3034) 
(list 1599.4375 -199.117)))
(apply 'command (append '("pline") coords '("c")))
(setq currobj (ssadd (entlast) currobj))
(setq coords (list 
(list 1599.4375 -199.26) 
(list 1525.415 -210.4464) 
(list 1525.415 -210.6234) 
(list 1599.4375 -199.337)))
(apply 'command (append '("pline") coords '("c")))
(setq currobj (ssadd (entlast) currobj))
(setq coords (list 
(list 1599.4375 -199.48) 
(list 1525.415 -210.7664) 
(list 1525.415 -210.9434) 
(list 1599.4375 -199.557)))
(apply 'command (append '("pline") coords '("c")))
(setq currobj (ssadd (entlast) currobj))
(setq coords (list 
(list 1599.4375 -199.7) 
(list 1525.415 -211.0864) 
(list 1525.415 -211.2634) 
(list 1599.4375 -199.777)))
(apply 'command (append '("pline") coords '("c")))
(setq currobj (ssadd (entlast) currobj))
(setq coords (list 
(list 1599.4375 -199.92) 
(list 1525.415 -211.4064) 
(list 1525.415 -211.5834) 
(list 1599.4375 -199.997)))
(apply 'command (append '("pline") coords '("c")))
(setq currobj (ssadd (entlast) currobj))
(setq coords (list 
(list 1599.4375 -200.14) 
(list 1525.415 -211.7264) 
(list 1525.415 -211.9034) 
(list 1599.4375 -200.217)))
(apply 'command (append '("pline") coords '("c")))
(setq currobj (ssadd (entlast) currobj))
(setq coords (list 
(list 1599.4375 -200.36) 
(list 1525.415 -212.0464) 
(list 1525.415 -212.2234) 
(list 1599.4375 -200.437)))
(apply 'command (append '("pline") coords '("c")))
(setq currobj (ssadd (entlast) currobj))
(setq coords (list 
(list 1599.4375 -200.58) 
(list 1525.415 -212.3664) 
(list 1525.415 -212.5434) 
(list 1599.4375 -200.657)))
(apply 'command (append '("pline") coords '("c")))
(setq currobj (ssadd (entlast) currobj))
(command "_layer" "set" "nitride" "")
(command "_layer" "set" "text" "")
(command "_circle" "1598.985,-211.8" "0.075")
(command "_circle" "1598.985,-211.5" "0.075")
(command "_circle" "1598.985,-211.2" "0.075")
(command "_circle" "1598.985,-210.9" "0.075")
(command "_circle" "1598.985,-210.6" "0.075")
(command "_circle" "1598.685,-211.8" "0.075")
(command "_circle" "1598.685,-211.5" "0.075")
(command "_circle" "1598.685,-211.2" "0.075")
(command "_circle" "1598.685,-210.9" "0.075")
(command "_circle" "1598.685,-210.6" "0.075")
(command "_circle" "1598.385,-211.8" "0.075")
(command "_circle" "1598.385,-211.5" "0.075")
(command "_circle" "1598.385,-211.2" "0.075")
(command "_circle" "1598.385,-210.9" "0.075")
(command "_circle" "1598.385,-210.6" "0.075")
(command "_circle" "1598.085,-211.8" "0.075")
(command "_circle" "1598.085,-211.5" "0.075")
(command "_circle" "1598.085,-211.2" "0.075")
(command "_circle" "1598.085,-210.9" "0.075")
(command "_circle" "1598.085,-210.6" "0.075")
(command "_circle" "1597.785,-211.8" "0.075")
(command "_circle" "1597.785,-211.5" "0.075")
(command "_circle" "1597.785,-211.2" "0.075")
(command "_circle" "1597.785,-210.9" "0.075")
(command "_circle" "1597.785,-210.6" "0.075")
(command "_layer" "set" "nitride" "")
(setq anglednodearray5 currobj)
(setq currobj nil)
(setq currobj (ssadd))
; DRAWING COOLED SINGLE NANOBEAM
(setq coords (list 
(list 1600.2625 -186.357) 
(list 1600.2625 -181.357) 
(list 1599.7375 -181.357) 
(list 1599.7375 -186.357)))
(apply 'command (append '("pline") coords '("c")))
(setq currobj (ssadd (entlast) currobj))
(command "_layer" "set" "prebias" "")
(command "_rectangle" "1599.7375,-186.357" "1600.2625,-181.357")
(setq currobj (ssadd (entlast) currobj))
(command "_layer" "set" "nitride" "")
(setq coords (list 
(list 1600.2625 -181.357) 
(list 1600.5625 -171.357) 
(list 1600.5625 -171.357) 
(list 1600.5625 -170.357) 
(list 1674.585 -171.107) 
(list 1674.585 -166.164) 
(list 1600.5625 -166.914) 
(list 1600.5625 -165.914) 
(list 1600.5625 -165.914) 
(list 1600.2625 -155.914) 
(list 1599.7375 -155.914) 
(list 1599.4375 -165.914) 
(list 1599.4375 -165.914) 
(list 1599.4375 -166.914) 
(list 1525.415 -166.164) 
(list 1525.415 -171.107) 
(list 1599.4375 -170.357) 
(list 1599.4375 -171.357) 
(list 1599.4375 -171.357) 
(list 1599.7375 -181.357)))
(apply 'command (append '("pline") coords '("c")))
(setq currobj (ssadd (entlast) currobj))
(command "_layer" "set" "prebias" "")
(setq coords (list 
(list 1599.4375 -181.357) 
(list 1599.4375 -170.357) 
(list 1525.415 -171.107) 
(list 1525.415 -166.164) 
(list 1599.4375 -166.914) 
(list 1599.4375 -155.914) 
(list 1600.5625 -155.914) 
(list 1600.5625 -166.914) 
(list 1674.585 -166.164) 
(list 1674.585 -171.107) 
(list 1600.5625 -170.357) 
(list 1600.5625 -181.357)))
(apply 'command (append '("pline") coords '("c")))
(setq currobj (ssadd (entlast) currobj))
(command "_layer" "set" "nitride" "")
(command "_layer" "set" "fda1" "")
(setq coords (list 
(list 1600.5625 -170.214) 
(list 1674.585 -170.964) 
(list 1674.585 -170.787) 
(list 1600.5625 -170.137)))
(apply 'command (append '("pline") coords '("c")))
(setq currobj (ssadd (entlast) currobj))
(setq coords (list 
(list 1600.5625 -169.994) 
(list 1674.585 -170.644) 
(list 1674.585 -170.467) 
(list 1600.5625 -169.917)))
(apply 'command (append '("pline") coords '("c")))
(setq currobj (ssadd (entlast) currobj))
(setq coords (list 
(list 1600.5625 -169.774) 
(list 1674.585 -170.324) 
(list 1674.585 -170.147) 
(list 1600.5625 -169.697)))
(apply 'command (append '("pline") coords '("c")))
(setq currobj (ssadd (entlast) currobj))
(setq coords (list 
(list 1600.5625 -169.554) 
(list 1674.585 -170.004) 
(list 1674.585 -169.827) 
(list 1600.5625 -169.477)))
(apply 'command (append '("pline") coords '("c")))
(setq currobj (ssadd (entlast) currobj))
(setq coords (list 
(list 1600.5625 -169.334) 
(list 1674.585 -169.684) 
(list 1674.585 -169.507) 
(list 1600.5625 -169.257)))
(apply 'command (append '("pline") coords '("c")))
(setq currobj (ssadd (entlast) currobj))
(setq coords (list 
(list 1600.5625 -169.114) 
(list 1674.585 -169.364) 
(list 1674.585 -169.187) 
(list 1600.5625 -169.037)))
(apply 'command (append '("pline") coords '("c")))
(setq currobj (ssadd (entlast) currobj))
(setq coords (list 
(list 1600.5625 -168.894) 
(list 1674.585 -169.044) 
(list 1674.585 -168.867) 
(list 1600.5625 -168.817)))
(apply 'command (append '("pline") coords '("c")))
(setq currobj (ssadd (entlast) currobj))
(setq coords (list 
(list 1600.5625 -168.674) 
(list 1674.585 -168.724) 
(list 1674.585 -168.547) 
(list 1600.5625 -168.597)))
(apply 'command (append '("pline") coords '("c")))
(setq currobj (ssadd (entlast) currobj))
(setq coords (list 
(list 1600.5625 -168.454) 
(list 1674.585 -168.404) 
(list 1674.585 -168.227) 
(list 1600.5625 -168.377)))
(apply 'command (append '("pline") coords '("c")))
(setq currobj (ssadd (entlast) currobj))
(setq coords (list 
(list 1600.5625 -168.234) 
(list 1674.585 -168.084) 
(list 1674.585 -167.907) 
(list 1600.5625 -168.157)))
(apply 'command (append '("pline") coords '("c")))
(setq currobj (ssadd (entlast) currobj))
(setq coords (list 
(list 1600.5625 -168.014) 
(list 1674.585 -167.764) 
(list 1674.585 -167.587) 
(list 1600.5625 -167.937)))
(apply 'command (append '("pline") coords '("c")))
(setq currobj (ssadd (entlast) currobj))
(setq coords (list 
(list 1600.5625 -167.794) 
(list 1674.585 -167.444) 
(list 1674.585 -167.267) 
(list 1600.5625 -167.717)))
(apply 'command (append '("pline") coords '("c")))
(setq currobj (ssadd (entlast) currobj))
(setq coords (list 
(list 1600.5625 -167.574) 
(list 1674.585 -167.124) 
(list 1674.585 -166.947) 
(list 1600.5625 -167.497)))
(apply 'command (append '("pline") coords '("c")))
(setq currobj (ssadd (entlast) currobj))
(setq coords (list 
(list 1600.5625 -167.354) 
(list 1674.585 -166.804) 
(list 1674.585 -166.627) 
(list 1600.5625 -167.277)))
(apply 'command (append '("pline") coords '("c")))
(setq currobj (ssadd (entlast) currobj))
(setq coords (list 
(list 1600.5625 -167.134) 
(list 1674.585 -166.484) 
(list 1674.585 -166.307) 
(list 1600.5625 -167.057)))
(apply 'command (append '("pline") coords '("c")))
(setq currobj (ssadd (entlast) currobj))
(setq coords (list 
(list 1599.4375 -167.057) 
(list 1525.415 -166.307) 
(list 1525.415 -166.484) 
(list 1599.4375 -167.134)))
(apply 'command (append '("pline") coords '("c")))
(setq currobj (ssadd (entlast) currobj))
(setq coords (list 
(list 1599.4375 -167.277) 
(list 1525.415 -166.627) 
(list 1525.415 -166.804) 
(list 1599.4375 -167.354)))
(apply 'command (append '("pline") coords '("c")))
(setq currobj (ssadd (entlast) currobj))
(setq coords (list 
(list 1599.4375 -167.497) 
(list 1525.415 -166.947) 
(list 1525.415 -167.124) 
(list 1599.4375 -167.574)))
(apply 'command (append '("pline") coords '("c")))
(setq currobj (ssadd (entlast) currobj))
(setq coords (list 
(list 1599.4375 -167.717) 
(list 1525.415 -167.267) 
(list 1525.415 -167.444) 
(list 1599.4375 -167.794)))
(apply 'command (append '("pline") coords '("c")))
(setq currobj (ssadd (entlast) currobj))
(setq coords (list 
(list 1599.4375 -167.937) 
(list 1525.415 -167.587) 
(list 1525.415 -167.764) 
(list 1599.4375 -168.014)))
(apply 'command (append '("pline") coords '("c")))
(setq currobj (ssadd (entlast) currobj))
(setq coords (list 
(list 1599.4375 -168.157) 
(list 1525.415 -167.907) 
(list 1525.415 -168.084) 
(list 1599.4375 -168.234)))
(apply 'command (append '("pline") coords '("c")))
(setq currobj (ssadd (entlast) currobj))
(setq coords (list 
(list 1599.4375 -168.377) 
(list 1525.415 -168.227) 
(list 1525.415 -168.404) 
(list 1599.4375 -168.454)))
(apply 'command (append '("pline") coords '("c")))
(setq currobj (ssadd (entlast) currobj))
(setq coords (list 
(list 1599.4375 -168.597) 
(list 1525.415 -168.547) 
(list 1525.415 -168.724) 
(list 1599.4375 -168.674)))
(apply 'command (append '("pline") coords '("c")))
(setq currobj (ssadd (entlast) currobj))
(setq coords (list 
(list 1599.4375 -168.817) 
(list 1525.415 -168.867) 
(list 1525.415 -169.044) 
(list 1599.4375 -168.894)))
(apply 'command (append '("pline") coords '("c")))
(setq currobj (ssadd (entlast) currobj))
(setq coords (list 
(list 1599.4375 -169.037) 
(list 1525.415 -169.187) 
(list 1525.415 -169.364) 
(list 1599.4375 -169.114)))
(apply 'command (append '("pline") coords '("c")))
(setq currobj (ssadd (entlast) currobj))
(setq coords (list 
(list 1599.4375 -169.257) 
(list 1525.415 -169.507) 
(list 1525.415 -169.684) 
(list 1599.4375 -169.334)))
(apply 'command (append '("pline") coords '("c")))
(setq currobj (ssadd (entlast) currobj))
(setq coords (list 
(list 1599.4375 -169.477) 
(list 1525.415 -169.827) 
(list 1525.415 -170.004) 
(list 1599.4375 -169.554)))
(apply 'command (append '("pline") coords '("c")))
(setq currobj (ssadd (entlast) currobj))
(setq coords (list 
(list 1599.4375 -169.697) 
(list 1525.415 -170.147) 
(list 1525.415 -170.324) 
(list 1599.4375 -169.774)))
(apply 'command (append '("pline") coords '("c")))
(setq currobj (ssadd (entlast) currobj))
(setq coords (list 
(list 1599.4375 -169.917) 
(list 1525.415 -170.467) 
(list 1525.415 -170.644) 
(list 1599.4375 -169.994)))
(apply 'command (append '("pline") coords '("c")))
(setq currobj (ssadd (entlast) currobj))
(setq coords (list 
(list 1599.4375 -170.137) 
(list 1525.415 -170.787) 
(list 1525.415 -170.964) 
(list 1599.4375 -170.214)))
(apply 'command (append '("pline") coords '("c")))
(setq currobj (ssadd (entlast) currobj))
(command "_layer" "set" "nitride" "")
(command "_layer" "set" "text" "")
(command "_circle" "1599.0625,-181.357" "0.075")
(command "_circle" "1599.0625,-181.057" "0.075")
(command "_circle" "1599.0625,-180.757" "0.075")
(command "_circle" "1599.0625,-180.457" "0.075")
(command "_circle" "1599.0625,-180.157" "0.075")
(command "_circle" "1598.7625,-181.357" "0.075")
(command "_circle" "1598.7625,-181.057" "0.075")
(command "_circle" "1598.7625,-180.757" "0.075")
(command "_circle" "1598.7625,-180.457" "0.075")
(command "_circle" "1598.7625,-180.157" "0.075")
(command "_circle" "1598.4625,-181.357" "0.075")
(command "_circle" "1598.4625,-181.057" "0.075")
(command "_circle" "1598.4625,-180.757" "0.075")
(command "_circle" "1598.4625,-180.457" "0.075")
(command "_circle" "1598.4625,-180.157" "0.075")
(command "_circle" "1598.1625,-181.357" "0.075")
(command "_circle" "1598.1625,-181.057" "0.075")
(command "_circle" "1598.1625,-180.757" "0.075")
(command "_circle" "1598.1625,-180.457" "0.075")
(command "_circle" "1598.1625,-180.157" "0.075")
(command "_circle" "1597.8625,-181.357" "0.075")
(command "_circle" "1597.8625,-181.057" "0.075")
(command "_circle" "1597.8625,-180.757" "0.075")
(command "_circle" "1597.8625,-180.457" "0.075")
(command "_circle" "1597.8625,-180.157" "0.075")
(command "_layer" "set" "nitride" "")
(setq coords (list 
(list 1600.2625 -155.914) 
(list 1600.2625 -40.2693) 
(list 1599.7375 -40.2693) 
(list 1599.7375 -155.914)))
(apply 'command (append '("pline") coords '("c")))
(setq currobj (ssadd (entlast) currobj))
(command "_layer" "set" "prebias" "")
(command "_rectangle" "1599.7375,-155.914" "1600.2625,-40.2693")
(setq currobj (ssadd (entlast) currobj))
(command "_layer" "set" "nitride" "")
(setq coords (list 
(list 1600.2625 -40.2693) 
(list 1600.5625 -30.2693) 
(list 1600.5625 -30.2693) 
(list 1600.5625 -29.2693) 
(list 1674.585 -30.0193) 
(list 1674.585 -25.0763) 
(list 1600.5625 -25.8263) 
(list 1600.5625 -24.8263) 
(list 1600.5625 -24.8263) 
(list 1600.2625 -14.8263) 
(list 1599.7375 -14.8263) 
(list 1599.4375 -24.8263) 
(list 1599.4375 -24.8263) 
(list 1599.4375 -25.8263) 
(list 1525.415 -25.0763) 
(list 1525.415 -30.0193) 
(list 1599.4375 -29.2693) 
(list 1599.4375 -30.2693) 
(list 1599.4375 -30.2693) 
(list 1599.7375 -40.2693)))
(apply 'command (append '("pline") coords '("c")))
(setq currobj (ssadd (entlast) currobj))
(command "_layer" "set" "prebias" "")
(setq coords (list 
(list 1599.4375 -40.2693) 
(list 1599.4375 -29.2693) 
(list 1525.415 -30.0193) 
(list 1525.415 -25.0763) 
(list 1599.4375 -25.8263) 
(list 1599.4375 -14.8263) 
(list 1600.5625 -14.8263) 
(list 1600.5625 -25.8263) 
(list 1674.585 -25.0763) 
(list 1674.585 -30.0193) 
(list 1600.5625 -29.2693) 
(list 1600.5625 -40.2693)))
(apply 'command (append '("pline") coords '("c")))
(setq currobj (ssadd (entlast) currobj))
(command "_layer" "set" "nitride" "")
(command "_layer" "set" "fda1" "")
(setq coords (list 
(list 1600.5625 -29.1263) 
(list 1674.585 -29.8763) 
(list 1674.585 -29.6993) 
(list 1600.5625 -29.0493)))
(apply 'command (append '("pline") coords '("c")))
(setq currobj (ssadd (entlast) currobj))
(setq coords (list 
(list 1600.5625 -28.9063) 
(list 1674.585 -29.5563) 
(list 1674.585 -29.3793) 
(list 1600.5625 -28.8293)))
(apply 'command (append '("pline") coords '("c")))
(setq currobj (ssadd (entlast) currobj))
(setq coords (list 
(list 1600.5625 -28.6863) 
(list 1674.585 -29.2363) 
(list 1674.585 -29.0593) 
(list 1600.5625 -28.6093)))
(apply 'command (append '("pline") coords '("c")))
(setq currobj (ssadd (entlast) currobj))
(setq coords (list 
(list 1600.5625 -28.4663) 
(list 1674.585 -28.9163) 
(list 1674.585 -28.7393) 
(list 1600.5625 -28.3893)))
(apply 'command (append '("pline") coords '("c")))
(setq currobj (ssadd (entlast) currobj))
(setq coords (list 
(list 1600.5625 -28.2463) 
(list 1674.585 -28.5963) 
(list 1674.585 -28.4193) 
(list 1600.5625 -28.1693)))
(apply 'command (append '("pline") coords '("c")))
(setq currobj (ssadd (entlast) currobj))
(setq coords (list 
(list 1600.5625 -28.0263) 
(list 1674.585 -28.2763) 
(list 1674.585 -28.0993) 
(list 1600.5625 -27.9493)))
(apply 'command (append '("pline") coords '("c")))
(setq currobj (ssadd (entlast) currobj))
(setq coords (list 
(list 1600.5625 -27.8063) 
(list 1674.585 -27.9563) 
(list 1674.585 -27.7793) 
(list 1600.5625 -27.7293)))
(apply 'command (append '("pline") coords '("c")))
(setq currobj (ssadd (entlast) currobj))
(setq coords (list 
(list 1600.5625 -27.5863) 
(list 1674.585 -27.6363) 
(list 1674.585 -27.4593) 
(list 1600.5625 -27.5093)))
(apply 'command (append '("pline") coords '("c")))
(setq currobj (ssadd (entlast) currobj))
(setq coords (list 
(list 1600.5625 -27.3663) 
(list 1674.585 -27.3163) 
(list 1674.585 -27.1393) 
(list 1600.5625 -27.2893)))
(apply 'command (append '("pline") coords '("c")))
(setq currobj (ssadd (entlast) currobj))
(setq coords (list 
(list 1600.5625 -27.1463) 
(list 1674.585 -26.9963) 
(list 1674.585 -26.8193) 
(list 1600.5625 -27.0693)))
(apply 'command (append '("pline") coords '("c")))
(setq currobj (ssadd (entlast) currobj))
(setq coords (list 
(list 1600.5625 -26.9263) 
(list 1674.585 -26.6763) 
(list 1674.585 -26.4993) 
(list 1600.5625 -26.8493)))
(apply 'command (append '("pline") coords '("c")))
(setq currobj (ssadd (entlast) currobj))
(setq coords (list 
(list 1600.5625 -26.7063) 
(list 1674.585 -26.3563) 
(list 1674.585 -26.1793) 
(list 1600.5625 -26.6293)))
(apply 'command (append '("pline") coords '("c")))
(setq currobj (ssadd (entlast) currobj))
(setq coords (list 
(list 1600.5625 -26.4863) 
(list 1674.585 -26.0363) 
(list 1674.585 -25.8593) 
(list 1600.5625 -26.4093)))
(apply 'command (append '("pline") coords '("c")))
(setq currobj (ssadd (entlast) currobj))
(setq coords (list 
(list 1600.5625 -26.2663) 
(list 1674.585 -25.7163) 
(list 1674.585 -25.5393) 
(list 1600.5625 -26.1893)))
(apply 'command (append '("pline") coords '("c")))
(setq currobj (ssadd (entlast) currobj))
(setq coords (list 
(list 1600.5625 -26.0463) 
(list 1674.585 -25.3963) 
(list 1674.585 -25.2193) 
(list 1600.5625 -25.9693)))
(apply 'command (append '("pline") coords '("c")))
(setq currobj (ssadd (entlast) currobj))
(setq coords (list 
(list 1599.4375 -25.9693) 
(list 1525.415 -25.2193) 
(list 1525.415 -25.3963) 
(list 1599.4375 -26.0463)))
(apply 'command (append '("pline") coords '("c")))
(setq currobj (ssadd (entlast) currobj))
(setq coords (list 
(list 1599.4375 -26.1893) 
(list 1525.415 -25.5393) 
(list 1525.415 -25.7163) 
(list 1599.4375 -26.2663)))
(apply 'command (append '("pline") coords '("c")))
(setq currobj (ssadd (entlast) currobj))
(setq coords (list 
(list 1599.4375 -26.4093) 
(list 1525.415 -25.8593) 
(list 1525.415 -26.0363) 
(list 1599.4375 -26.4863)))
(apply 'command (append '("pline") coords '("c")))
(setq currobj (ssadd (entlast) currobj))
(setq coords (list 
(list 1599.4375 -26.6293) 
(list 1525.415 -26.1793) 
(list 1525.415 -26.3563) 
(list 1599.4375 -26.7063)))
(apply 'command (append '("pline") coords '("c")))
(setq currobj (ssadd (entlast) currobj))
(setq coords (list 
(list 1599.4375 -26.8493) 
(list 1525.415 -26.4993) 
(list 1525.415 -26.6763) 
(list 1599.4375 -26.9263)))
(apply 'command (append '("pline") coords '("c")))
(setq currobj (ssadd (entlast) currobj))
(setq coords (list 
(list 1599.4375 -27.0693) 
(list 1525.415 -26.8193) 
(list 1525.415 -26.9963) 
(list 1599.4375 -27.1463)))
(apply 'command (append '("pline") coords '("c")))
(setq currobj (ssadd (entlast) currobj))
(setq coords (list 
(list 1599.4375 -27.2893) 
(list 1525.415 -27.1393) 
(list 1525.415 -27.3163) 
(list 1599.4375 -27.3663)))
(apply 'command (append '("pline") coords '("c")))
(setq currobj (ssadd (entlast) currobj))
(setq coords (list 
(list 1599.4375 -27.5093) 
(list 1525.415 -27.4593) 
(list 1525.415 -27.6363) 
(list 1599.4375 -27.5863)))
(apply 'command (append '("pline") coords '("c")))
(setq currobj (ssadd (entlast) currobj))
(setq coords (list 
(list 1599.4375 -27.7293) 
(list 1525.415 -27.7793) 
(list 1525.415 -27.9563) 
(list 1599.4375 -27.8063)))
(apply 'command (append '("pline") coords '("c")))
(setq currobj (ssadd (entlast) currobj))
(setq coords (list 
(list 1599.4375 -27.9493) 
(list 1525.415 -28.0993) 
(list 1525.415 -28.2763) 
(list 1599.4375 -28.0263)))
(apply 'command (append '("pline") coords '("c")))
(setq currobj (ssadd (entlast) currobj))
(setq coords (list 
(list 1599.4375 -28.1693) 
(list 1525.415 -28.4193) 
(list 1525.415 -28.5963) 
(list 1599.4375 -28.2463)))
(apply 'command (append '("pline") coords '("c")))
(setq currobj (ssadd (entlast) currobj))
(setq coords (list 
(list 1599.4375 -28.3893) 
(list 1525.415 -28.7393) 
(list 1525.415 -28.9163) 
(list 1599.4375 -28.4663)))
(apply 'command (append '("pline") coords '("c")))
(setq currobj (ssadd (entlast) currobj))
(setq coords (list 
(list 1599.4375 -28.6093) 
(list 1525.415 -29.0593) 
(list 1525.415 -29.2363) 
(list 1599.4375 -28.6863)))
(apply 'command (append '("pline") coords '("c")))
(setq currobj (ssadd (entlast) currobj))
(setq coords (list 
(list 1599.4375 -28.8293) 
(list 1525.415 -29.3793) 
(list 1525.415 -29.5563) 
(list 1599.4375 -28.9063)))
(apply 'command (append '("pline") coords '("c")))
(setq currobj (ssadd (entlast) currobj))
(setq coords (list 
(list 1599.4375 -29.0493) 
(list 1525.415 -29.6993) 
(list 1525.415 -29.8763) 
(list 1599.4375 -29.1263)))
(apply 'command (append '("pline") coords '("c")))
(setq currobj (ssadd (entlast) currobj))
(command "_layer" "set" "nitride" "")
(command "_layer" "set" "text" "")
(command "_circle" "1599.0625,-40.2693" "0.075")
(command "_circle" "1599.0625,-39.9693" "0.075")
(command "_circle" "1599.0625,-39.6693" "0.075")
(command "_circle" "1599.0625,-39.3693" "0.075")
(command "_circle" "1599.0625,-39.0693" "0.075")
(command "_circle" "1598.7625,-40.2693" "0.075")
(command "_circle" "1598.7625,-39.9693" "0.075")
(command "_circle" "1598.7625,-39.6693" "0.075")
(command "_circle" "1598.7625,-39.3693" "0.075")
(command "_circle" "1598.7625,-39.0693" "0.075")
(command "_circle" "1598.4625,-40.2693" "0.075")
(command "_circle" "1598.4625,-39.9693" "0.075")
(command "_circle" "1598.4625,-39.6693" "0.075")
(command "_circle" "1598.4625,-39.3693" "0.075")
(command "_circle" "1598.4625,-39.0693" "0.075")
(command "_circle" "1598.1625,-40.2693" "0.075")
(command "_circle" "1598.1625,-39.9693" "0.075")
(command "_circle" "1598.1625,-39.6693" "0.075")
(command "_circle" "1598.1625,-39.3693" "0.075")
(command "_circle" "1598.1625,-39.0693" "0.075")
(command "_circle" "1597.8625,-40.2693" "0.075")
(command "_circle" "1597.8625,-39.9693" "0.075")
(command "_circle" "1597.8625,-39.6693" "0.075")
(command "_circle" "1597.8625,-39.3693" "0.075")
(command "_circle" "1597.8625,-39.0693" "0.075")
(command "_layer" "set" "nitride" "")
(setq coords (list 
(list 1600.2625 -14.8263) 
(list 1600.2625 100.8184) 
(list 1599.7375 100.8184) 
(list 1599.7375 -14.8263)))
(apply 'command (append '("pline") coords '("c")))
(setq currobj (ssadd (entlast) currobj))
(command "_layer" "set" "prebias" "")
(command "_rectangle" "1599.7375,-14.8263" "1600.2625,100.8184")
(setq currobj (ssadd (entlast) currobj))
(command "_layer" "set" "nitride" "")
(setq coords (list 
(list 1600.2625 100.8184) 
(list 1600.5625 110.8184) 
(list 1600.5625 110.8184) 
(list 1600.5625 111.8184) 
(list 1674.585 111.0684) 
(list 1674.585 116.0114) 
(list 1600.5625 115.2614) 
(list 1600.5625 116.2614) 
(list 1600.5625 116.2614) 
(list 1600.2625 126.2614) 
(list 1599.7375 126.2614) 
(list 1599.4375 116.2614) 
(list 1599.4375 116.2614) 
(list 1599.4375 115.2614) 
(list 1525.415 116.0114) 
(list 1525.415 111.0684) 
(list 1599.4375 111.8184) 
(list 1599.4375 110.8184) 
(list 1599.4375 110.8184) 
(list 1599.7375 100.8184)))
(apply 'command (append '("pline") coords '("c")))
(setq currobj (ssadd (entlast) currobj))
(command "_layer" "set" "prebias" "")
(setq coords (list 
(list 1599.4375 100.8184) 
(list 1599.4375 111.8184) 
(list 1525.415 111.0684) 
(list 1525.415 116.0114) 
(list 1599.4375 115.2614) 
(list 1599.4375 126.2614) 
(list 1600.5625 126.2614) 
(list 1600.5625 115.2614) 
(list 1674.585 116.0114) 
(list 1674.585 111.0684) 
(list 1600.5625 111.8184) 
(list 1600.5625 100.8184)))
(apply 'command (append '("pline") coords '("c")))
(setq currobj (ssadd (entlast) currobj))
(command "_layer" "set" "nitride" "")
(command "_layer" "set" "fda1" "")
(setq coords (list 
(list 1600.5625 111.9614) 
(list 1674.585 111.2114) 
(list 1674.585 111.3884) 
(list 1600.5625 112.0384)))
(apply 'command (append '("pline") coords '("c")))
(setq currobj (ssadd (entlast) currobj))
(setq coords (list 
(list 1600.5625 112.1814) 
(list 1674.585 111.5314) 
(list 1674.585 111.7084) 
(list 1600.5625 112.2584)))
(apply 'command (append '("pline") coords '("c")))
(setq currobj (ssadd (entlast) currobj))
(setq coords (list 
(list 1600.5625 112.4014) 
(list 1674.585 111.8514) 
(list 1674.585 112.0284) 
(list 1600.5625 112.4784)))
(apply 'command (append '("pline") coords '("c")))
(setq currobj (ssadd (entlast) currobj))
(setq coords (list 
(list 1600.5625 112.6214) 
(list 1674.585 112.1714) 
(list 1674.585 112.3484) 
(list 1600.5625 112.6984)))
(apply 'command (append '("pline") coords '("c")))
(setq currobj (ssadd (entlast) currobj))
(setq coords (list 
(list 1600.5625 112.8414) 
(list 1674.585 112.4914) 
(list 1674.585 112.6684) 
(list 1600.5625 112.9184)))
(apply 'command (append '("pline") coords '("c")))
(setq currobj (ssadd (entlast) currobj))
(setq coords (list 
(list 1600.5625 113.0614) 
(list 1674.585 112.8114) 
(list 1674.585 112.9884) 
(list 1600.5625 113.1384)))
(apply 'command (append '("pline") coords '("c")))
(setq currobj (ssadd (entlast) currobj))
(setq coords (list 
(list 1600.5625 113.2814) 
(list 1674.585 113.1314) 
(list 1674.585 113.3084) 
(list 1600.5625 113.3584)))
(apply 'command (append '("pline") coords '("c")))
(setq currobj (ssadd (entlast) currobj))
(setq coords (list 
(list 1600.5625 113.5014) 
(list 1674.585 113.4514) 
(list 1674.585 113.6284) 
(list 1600.5625 113.5784)))
(apply 'command (append '("pline") coords '("c")))
(setq currobj (ssadd (entlast) currobj))
(setq coords (list 
(list 1600.5625 113.7214) 
(list 1674.585 113.7714) 
(list 1674.585 113.9484) 
(list 1600.5625 113.7984)))
(apply 'command (append '("pline") coords '("c")))
(setq currobj (ssadd (entlast) currobj))
(setq coords (list 
(list 1600.5625 113.9414) 
(list 1674.585 114.0914) 
(list 1674.585 114.2684) 
(list 1600.5625 114.0184)))
(apply 'command (append '("pline") coords '("c")))
(setq currobj (ssadd (entlast) currobj))
(setq coords (list 
(list 1600.5625 114.1614) 
(list 1674.585 114.4114) 
(list 1674.585 114.5884) 
(list 1600.5625 114.2384)))
(apply 'command (append '("pline") coords '("c")))
(setq currobj (ssadd (entlast) currobj))
(setq coords (list 
(list 1600.5625 114.3814) 
(list 1674.585 114.7314) 
(list 1674.585 114.9084) 
(list 1600.5625 114.4584)))
(apply 'command (append '("pline") coords '("c")))
(setq currobj (ssadd (entlast) currobj))
(setq coords (list 
(list 1600.5625 114.6014) 
(list 1674.585 115.0514) 
(list 1674.585 115.2284) 
(list 1600.5625 114.6784)))
(apply 'command (append '("pline") coords '("c")))
(setq currobj (ssadd (entlast) currobj))
(setq coords (list 
(list 1600.5625 114.8214) 
(list 1674.585 115.3714) 
(list 1674.585 115.5484) 
(list 1600.5625 114.8984)))
(apply 'command (append '("pline") coords '("c")))
(setq currobj (ssadd (entlast) currobj))
(setq coords (list 
(list 1600.5625 115.0414) 
(list 1674.585 115.6914) 
(list 1674.585 115.8684) 
(list 1600.5625 115.1184)))
(apply 'command (append '("pline") coords '("c")))
(setq currobj (ssadd (entlast) currobj))
(setq coords (list 
(list 1599.4375 115.1184) 
(list 1525.415 115.8684) 
(list 1525.415 115.6914) 
(list 1599.4375 115.0414)))
(apply 'command (append '("pline") coords '("c")))
(setq currobj (ssadd (entlast) currobj))
(setq coords (list 
(list 1599.4375 114.8984) 
(list 1525.415 115.5484) 
(list 1525.415 115.3714) 
(list 1599.4375 114.8214)))
(apply 'command (append '("pline") coords '("c")))
(setq currobj (ssadd (entlast) currobj))
(setq coords (list 
(list 1599.4375 114.6784) 
(list 1525.415 115.2284) 
(list 1525.415 115.0514) 
(list 1599.4375 114.6014)))
(apply 'command (append '("pline") coords '("c")))
(setq currobj (ssadd (entlast) currobj))
(setq coords (list 
(list 1599.4375 114.4584) 
(list 1525.415 114.9084) 
(list 1525.415 114.7314) 
(list 1599.4375 114.3814)))
(apply 'command (append '("pline") coords '("c")))
(setq currobj (ssadd (entlast) currobj))
(setq coords (list 
(list 1599.4375 114.2384) 
(list 1525.415 114.5884) 
(list 1525.415 114.4114) 
(list 1599.4375 114.1614)))
(apply 'command (append '("pline") coords '("c")))
(setq currobj (ssadd (entlast) currobj))
(setq coords (list 
(list 1599.4375 114.0184) 
(list 1525.415 114.2684) 
(list 1525.415 114.0914) 
(list 1599.4375 113.9414)))
(apply 'command (append '("pline") coords '("c")))
(setq currobj (ssadd (entlast) currobj))
(setq coords (list 
(list 1599.4375 113.7984) 
(list 1525.415 113.9484) 
(list 1525.415 113.7714) 
(list 1599.4375 113.7214)))
(apply 'command (append '("pline") coords '("c")))
(setq currobj (ssadd (entlast) currobj))
(setq coords (list 
(list 1599.4375 113.5784) 
(list 1525.415 113.6284) 
(list 1525.415 113.4514) 
(list 1599.4375 113.5014)))
(apply 'command (append '("pline") coords '("c")))
(setq currobj (ssadd (entlast) currobj))
(setq coords (list 
(list 1599.4375 113.3584) 
(list 1525.415 113.3084) 
(list 1525.415 113.1314) 
(list 1599.4375 113.2814)))
(apply 'command (append '("pline") coords '("c")))
(setq currobj (ssadd (entlast) currobj))
(setq coords (list 
(list 1599.4375 113.1384) 
(list 1525.415 112.9884) 
(list 1525.415 112.8114) 
(list 1599.4375 113.0614)))
(apply 'command (append '("pline") coords '("c")))
(setq currobj (ssadd (entlast) currobj))
(setq coords (list 
(list 1599.4375 112.9184) 
(list 1525.415 112.6684) 
(list 1525.415 112.4914) 
(list 1599.4375 112.8414)))
(apply 'command (append '("pline") coords '("c")))
(setq currobj (ssadd (entlast) currobj))
(setq coords (list 
(list 1599.4375 112.6984) 
(list 1525.415 112.3484) 
(list 1525.415 112.1714) 
(list 1599.4375 112.6214)))
(apply 'command (append '("pline") coords '("c")))
(setq currobj (ssadd (entlast) currobj))
(setq coords (list 
(list 1599.4375 112.4784) 
(list 1525.415 112.0284) 
(list 1525.415 111.8514) 
(list 1599.4375 112.4014)))
(apply 'command (append '("pline") coords '("c")))
(setq currobj (ssadd (entlast) currobj))
(setq coords (list 
(list 1599.4375 112.2584) 
(list 1525.415 111.7084) 
(list 1525.415 111.5314) 
(list 1599.4375 112.1814)))
(apply 'command (append '("pline") coords '("c")))
(setq currobj (ssadd (entlast) currobj))
(setq coords (list 
(list 1599.4375 112.0384) 
(list 1525.415 111.3884) 
(list 1525.415 111.2114) 
(list 1599.4375 111.9614)))
(apply 'command (append '("pline") coords '("c")))
(setq currobj (ssadd (entlast) currobj))
(command "_layer" "set" "nitride" "")
(command "_layer" "set" "text" "")
(command "_circle" "1599.0625,100.8184" "0.075")
(command "_circle" "1599.0625,101.1184" "0.075")
(command "_circle" "1599.0625,101.4184" "0.075")
(command "_circle" "1599.0625,101.7184" "0.075")
(command "_circle" "1599.0625,102.0184" "0.075")
(command "_circle" "1598.7625,100.8184" "0.075")
(command "_circle" "1598.7625,101.1184" "0.075")
(command "_circle" "1598.7625,101.4184" "0.075")
(command "_circle" "1598.7625,101.7184" "0.075")
(command "_circle" "1598.7625,102.0184" "0.075")
(command "_circle" "1598.4625,100.8184" "0.075")
(command "_circle" "1598.4625,101.1184" "0.075")
(command "_circle" "1598.4625,101.4184" "0.075")
(command "_circle" "1598.4625,101.7184" "0.075")
(command "_circle" "1598.4625,102.0184" "0.075")
(command "_circle" "1598.1625,100.8184" "0.075")
(command "_circle" "1598.1625,101.1184" "0.075")
(command "_circle" "1598.1625,101.4184" "0.075")
(command "_circle" "1598.1625,101.7184" "0.075")
(command "_circle" "1598.1625,102.0184" "0.075")
(command "_circle" "1597.8625,100.8184" "0.075")
(command "_circle" "1597.8625,101.1184" "0.075")
(command "_circle" "1597.8625,101.4184" "0.075")
(command "_circle" "1597.8625,101.7184" "0.075")
(command "_circle" "1597.8625,102.0184" "0.075")
(command "_layer" "set" "nitride" "")
(setq coords (list 
(list 1600.2625 126.2614) 
(list 1600.2625 241.9061) 
(list 1599.7375 241.9061) 
(list 1599.7375 126.2614)))
(apply 'command (append '("pline") coords '("c")))
(setq currobj (ssadd (entlast) currobj))
(command "_layer" "set" "prebias" "")
(command "_rectangle" "1599.7375,126.2614" "1600.2625,241.9061")
(setq currobj (ssadd (entlast) currobj))
(command "_layer" "set" "nitride" "")
(setq coords (list 
(list 1600.2625 241.9061) 
(list 1600.5625 251.9061) 
(list 1600.5625 251.9061) 
(list 1600.5625 252.9061) 
(list 1674.585 252.1561) 
(list 1674.585 257.0991) 
(list 1600.5625 256.3491) 
(list 1600.5625 257.3491) 
(list 1600.5625 257.3491) 
(list 1600.2625 267.3491) 
(list 1599.7375 267.3491) 
(list 1599.4375 257.3491) 
(list 1599.4375 257.3491) 
(list 1599.4375 256.3491) 
(list 1525.415 257.0991) 
(list 1525.415 252.1561) 
(list 1599.4375 252.9061) 
(list 1599.4375 251.9061) 
(list 1599.4375 251.9061) 
(list 1599.7375 241.9061)))
(apply 'command (append '("pline") coords '("c")))
(setq currobj (ssadd (entlast) currobj))
(command "_layer" "set" "prebias" "")
(setq coords (list 
(list 1599.4375 241.9061) 
(list 1599.4375 252.9061) 
(list 1525.415 252.1561) 
(list 1525.415 257.0991) 
(list 1599.4375 256.3491) 
(list 1599.4375 267.3491) 
(list 1600.5625 267.3491) 
(list 1600.5625 256.3491) 
(list 1674.585 257.0991) 
(list 1674.585 252.1561) 
(list 1600.5625 252.9061) 
(list 1600.5625 241.9061)))
(apply 'command (append '("pline") coords '("c")))
(setq currobj (ssadd (entlast) currobj))
(command "_layer" "set" "nitride" "")
(command "_layer" "set" "fda1" "")
(setq coords (list 
(list 1600.5625 253.0491) 
(list 1674.585 252.2991) 
(list 1674.585 252.4761) 
(list 1600.5625 253.1261)))
(apply 'command (append '("pline") coords '("c")))
(setq currobj (ssadd (entlast) currobj))
(setq coords (list 
(list 1600.5625 253.2691) 
(list 1674.585 252.6191) 
(list 1674.585 252.7961) 
(list 1600.5625 253.3461)))
(apply 'command (append '("pline") coords '("c")))
(setq currobj (ssadd (entlast) currobj))
(setq coords (list 
(list 1600.5625 253.4891) 
(list 1674.585 252.9391) 
(list 1674.585 253.1161) 
(list 1600.5625 253.5661)))
(apply 'command (append '("pline") coords '("c")))
(setq currobj (ssadd (entlast) currobj))
(setq coords (list 
(list 1600.5625 253.7091) 
(list 1674.585 253.2591) 
(list 1674.585 253.4361) 
(list 1600.5625 253.7861)))
(apply 'command (append '("pline") coords '("c")))
(setq currobj (ssadd (entlast) currobj))
(setq coords (list 
(list 1600.5625 253.9291) 
(list 1674.585 253.5791) 
(list 1674.585 253.7561) 
(list 1600.5625 254.0061)))
(apply 'command (append '("pline") coords '("c")))
(setq currobj (ssadd (entlast) currobj))
(setq coords (list 
(list 1600.5625 254.1491) 
(list 1674.585 253.8991) 
(list 1674.585 254.0761) 
(list 1600.5625 254.2261)))
(apply 'command (append '("pline") coords '("c")))
(setq currobj (ssadd (entlast) currobj))
(setq coords (list 
(list 1600.5625 254.3691) 
(list 1674.585 254.2191) 
(list 1674.585 254.3961) 
(list 1600.5625 254.4461)))
(apply 'command (append '("pline") coords '("c")))
(setq currobj (ssadd (entlast) currobj))
(setq coords (list 
(list 1600.5625 254.5891) 
(list 1674.585 254.5391) 
(list 1674.585 254.7161) 
(list 1600.5625 254.6661)))
(apply 'command (append '("pline") coords '("c")))
(setq currobj (ssadd (entlast) currobj))
(setq coords (list 
(list 1600.5625 254.8091) 
(list 1674.585 254.8591) 
(list 1674.585 255.0361) 
(list 1600.5625 254.8861)))
(apply 'command (append '("pline") coords '("c")))
(setq currobj (ssadd (entlast) currobj))
(setq coords (list 
(list 1600.5625 255.0291) 
(list 1674.585 255.1791) 
(list 1674.585 255.3561) 
(list 1600.5625 255.1061)))
(apply 'command (append '("pline") coords '("c")))
(setq currobj (ssadd (entlast) currobj))
(setq coords (list 
(list 1600.5625 255.2491) 
(list 1674.585 255.4991) 
(list 1674.585 255.6761) 
(list 1600.5625 255.3261)))
(apply 'command (append '("pline") coords '("c")))
(setq currobj (ssadd (entlast) currobj))
(setq coords (list 
(list 1600.5625 255.4691) 
(list 1674.585 255.8191) 
(list 1674.585 255.9961) 
(list 1600.5625 255.5461)))
(apply 'command (append '("pline") coords '("c")))
(setq currobj (ssadd (entlast) currobj))
(setq coords (list 
(list 1600.5625 255.6891) 
(list 1674.585 256.1391) 
(list 1674.585 256.3161) 
(list 1600.5625 255.7661)))
(apply 'command (append '("pline") coords '("c")))
(setq currobj (ssadd (entlast) currobj))
(setq coords (list 
(list 1600.5625 255.9091) 
(list 1674.585 256.4591) 
(list 1674.585 256.6361) 
(list 1600.5625 255.9861)))
(apply 'command (append '("pline") coords '("c")))
(setq currobj (ssadd (entlast) currobj))
(setq coords (list 
(list 1600.5625 256.1291) 
(list 1674.585 256.7791) 
(list 1674.585 256.9561) 
(list 1600.5625 256.2061)))
(apply 'command (append '("pline") coords '("c")))
(setq currobj (ssadd (entlast) currobj))
(setq coords (list 
(list 1599.4375 256.2061) 
(list 1525.415 256.9561) 
(list 1525.415 256.7791) 
(list 1599.4375 256.1291)))
(apply 'command (append '("pline") coords '("c")))
(setq currobj (ssadd (entlast) currobj))
(setq coords (list 
(list 1599.4375 255.9861) 
(list 1525.415 256.6361) 
(list 1525.415 256.4591) 
(list 1599.4375 255.9091)))
(apply 'command (append '("pline") coords '("c")))
(setq currobj (ssadd (entlast) currobj))
(setq coords (list 
(list 1599.4375 255.7661) 
(list 1525.415 256.3161) 
(list 1525.415 256.1391) 
(list 1599.4375 255.6891)))
(apply 'command (append '("pline") coords '("c")))
(setq currobj (ssadd (entlast) currobj))
(setq coords (list 
(list 1599.4375 255.5461) 
(list 1525.415 255.9961) 
(list 1525.415 255.8191) 
(list 1599.4375 255.4691)))
(apply 'command (append '("pline") coords '("c")))
(setq currobj (ssadd (entlast) currobj))
(setq coords (list 
(list 1599.4375 255.3261) 
(list 1525.415 255.6761) 
(list 1525.415 255.4991) 
(list 1599.4375 255.2491)))
(apply 'command (append '("pline") coords '("c")))
(setq currobj (ssadd (entlast) currobj))
(setq coords (list 
(list 1599.4375 255.1061) 
(list 1525.415 255.3561) 
(list 1525.415 255.1791) 
(list 1599.4375 255.0291)))
(apply 'command (append '("pline") coords '("c")))
(setq currobj (ssadd (entlast) currobj))
(setq coords (list 
(list 1599.4375 254.8861) 
(list 1525.415 255.0361) 
(list 1525.415 254.8591) 
(list 1599.4375 254.8091)))
(apply 'command (append '("pline") coords '("c")))
(setq currobj (ssadd (entlast) currobj))
(setq coords (list 
(list 1599.4375 254.6661) 
(list 1525.415 254.7161) 
(list 1525.415 254.5391) 
(list 1599.4375 254.5891)))
(apply 'command (append '("pline") coords '("c")))
(setq currobj (ssadd (entlast) currobj))
(setq coords (list 
(list 1599.4375 254.4461) 
(list 1525.415 254.3961) 
(list 1525.415 254.2191) 
(list 1599.4375 254.3691)))
(apply 'command (append '("pline") coords '("c")))
(setq currobj (ssadd (entlast) currobj))
(setq coords (list 
(list 1599.4375 254.2261) 
(list 1525.415 254.0761) 
(list 1525.415 253.8991) 
(list 1599.4375 254.1491)))
(apply 'command (append '("pline") coords '("c")))
(setq currobj (ssadd (entlast) currobj))
(setq coords (list 
(list 1599.4375 254.0061) 
(list 1525.415 253.7561) 
(list 1525.415 253.5791) 
(list 1599.4375 253.9291)))
(apply 'command (append '("pline") coords '("c")))
(setq currobj (ssadd (entlast) currobj))
(setq coords (list 
(list 1599.4375 253.7861) 
(list 1525.415 253.4361) 
(list 1525.415 253.2591) 
(list 1599.4375 253.7091)))
(apply 'command (append '("pline") coords '("c")))
(setq currobj (ssadd (entlast) currobj))
(setq coords (list 
(list 1599.4375 253.5661) 
(list 1525.415 253.1161) 
(list 1525.415 252.9391) 
(list 1599.4375 253.4891)))
(apply 'command (append '("pline") coords '("c")))
(setq currobj (ssadd (entlast) currobj))
(setq coords (list 
(list 1599.4375 253.3461) 
(list 1525.415 252.7961) 
(list 1525.415 252.6191) 
(list 1599.4375 253.2691)))
(apply 'command (append '("pline") coords '("c")))
(setq currobj (ssadd (entlast) currobj))
(setq coords (list 
(list 1599.4375 253.1261) 
(list 1525.415 252.4761) 
(list 1525.415 252.2991) 
(list 1599.4375 253.0491)))
(apply 'command (append '("pline") coords '("c")))
(setq currobj (ssadd (entlast) currobj))
(command "_layer" "set" "nitride" "")
(command "_layer" "set" "text" "")
(command "_circle" "1599.0625,241.9061" "0.075")
(command "_circle" "1599.0625,242.2061" "0.075")
(command "_circle" "1599.0625,242.5061" "0.075")
(command "_circle" "1599.0625,242.8061" "0.075")
(command "_circle" "1599.0625,243.1061" "0.075")
(command "_circle" "1598.7625,241.9061" "0.075")
(command "_circle" "1598.7625,242.2061" "0.075")
(command "_circle" "1598.7625,242.5061" "0.075")
(command "_circle" "1598.7625,242.8061" "0.075")
(command "_circle" "1598.7625,243.1061" "0.075")
(command "_circle" "1598.4625,241.9061" "0.075")
(command "_circle" "1598.4625,242.2061" "0.075")
(command "_circle" "1598.4625,242.5061" "0.075")
(command "_circle" "1598.4625,242.8061" "0.075")
(command "_circle" "1598.4625,243.1061" "0.075")
(command "_circle" "1598.1625,241.9061" "0.075")
(command "_circle" "1598.1625,242.2061" "0.075")
(command "_circle" "1598.1625,242.5061" "0.075")
(command "_circle" "1598.1625,242.8061" "0.075")
(command "_circle" "1598.1625,243.1061" "0.075")
(command "_circle" "1597.8625,241.9061" "0.075")
(command "_circle" "1597.8625,242.2061" "0.075")
(command "_circle" "1597.8625,242.5061" "0.075")
(command "_circle" "1597.8625,242.8061" "0.075")
(command "_circle" "1597.8625,243.1061" "0.075")
(command "_layer" "set" "nitride" "")
(setq coords (list 
(list 1600.2625 267.3491) 
(list 1600.2625 382.9939) 
(list 1599.7375 382.9939) 
(list 1599.7375 267.3491)))
(apply 'command (append '("pline") coords '("c")))
(setq currobj (ssadd (entlast) currobj))
(command "_layer" "set" "prebias" "")
(command "_rectangle" "1599.7375,267.3491" "1600.2625,382.9939")
(setq currobj (ssadd (entlast) currobj))
(command "_layer" "set" "nitride" "")
(setq coords (list 
(list 1600.2625 382.9939) 
(list 1600.5625 392.9939) 
(list 1600.5625 392.9939) 
(list 1600.5625 393.9939) 
(list 1674.585 393.2439) 
(list 1674.585 398.1869) 
(list 1600.5625 397.4369) 
(list 1600.5625 398.4369) 
(list 1600.5625 398.4369) 
(list 1600.2625 408.4369) 
(list 1599.7375 408.4369) 
(list 1599.4375 398.4369) 
(list 1599.4375 398.4369) 
(list 1599.4375 397.4369) 
(list 1525.415 398.1869) 
(list 1525.415 393.2439) 
(list 1599.4375 393.9939) 
(list 1599.4375 392.9939) 
(list 1599.4375 392.9939) 
(list 1599.7375 382.9939)))
(apply 'command (append '("pline") coords '("c")))
(setq currobj (ssadd (entlast) currobj))
(command "_layer" "set" "prebias" "")
(setq coords (list 
(list 1599.4375 382.9939) 
(list 1599.4375 393.9939) 
(list 1525.415 393.2439) 
(list 1525.415 398.1869) 
(list 1599.4375 397.4369) 
(list 1599.4375 408.4369) 
(list 1600.5625 408.4369) 
(list 1600.5625 397.4369) 
(list 1674.585 398.1869) 
(list 1674.585 393.2439) 
(list 1600.5625 393.9939) 
(list 1600.5625 382.9939)))
(apply 'command (append '("pline") coords '("c")))
(setq currobj (ssadd (entlast) currobj))
(command "_layer" "set" "nitride" "")
(command "_layer" "set" "fda1" "")
(setq coords (list 
(list 1600.5625 394.1369) 
(list 1674.585 393.3869) 
(list 1674.585 393.5639) 
(list 1600.5625 394.2139)))
(apply 'command (append '("pline") coords '("c")))
(setq currobj (ssadd (entlast) currobj))
(setq coords (list 
(list 1600.5625 394.3569) 
(list 1674.585 393.7069) 
(list 1674.585 393.8839) 
(list 1600.5625 394.4339)))
(apply 'command (append '("pline") coords '("c")))
(setq currobj (ssadd (entlast) currobj))
(setq coords (list 
(list 1600.5625 394.5769) 
(list 1674.585 394.0269) 
(list 1674.585 394.2039) 
(list 1600.5625 394.6539)))
(apply 'command (append '("pline") coords '("c")))
(setq currobj (ssadd (entlast) currobj))
(setq coords (list 
(list 1600.5625 394.7969) 
(list 1674.585 394.3469) 
(list 1674.585 394.5239) 
(list 1600.5625 394.8739)))
(apply 'command (append '("pline") coords '("c")))
(setq currobj (ssadd (entlast) currobj))
(setq coords (list 
(list 1600.5625 395.0169) 
(list 1674.585 394.6669) 
(list 1674.585 394.8439) 
(list 1600.5625 395.0939)))
(apply 'command (append '("pline") coords '("c")))
(setq currobj (ssadd (entlast) currobj))
(setq coords (list 
(list 1600.5625 395.2369) 
(list 1674.585 394.9869) 
(list 1674.585 395.1639) 
(list 1600.5625 395.3139)))
(apply 'command (append '("pline") coords '("c")))
(setq currobj (ssadd (entlast) currobj))
(setq coords (list 
(list 1600.5625 395.4569) 
(list 1674.585 395.3069) 
(list 1674.585 395.4839) 
(list 1600.5625 395.5339)))
(apply 'command (append '("pline") coords '("c")))
(setq currobj (ssadd (entlast) currobj))
(setq coords (list 
(list 1600.5625 395.6769) 
(list 1674.585 395.6269) 
(list 1674.585 395.8039) 
(list 1600.5625 395.7539)))
(apply 'command (append '("pline") coords '("c")))
(setq currobj (ssadd (entlast) currobj))
(setq coords (list 
(list 1600.5625 395.8969) 
(list 1674.585 395.9469) 
(list 1674.585 396.1239) 
(list 1600.5625 395.9739)))
(apply 'command (append '("pline") coords '("c")))
(setq currobj (ssadd (entlast) currobj))
(setq coords (list 
(list 1600.5625 396.1169) 
(list 1674.585 396.2669) 
(list 1674.585 396.4439) 
(list 1600.5625 396.1939)))
(apply 'command (append '("pline") coords '("c")))
(setq currobj (ssadd (entlast) currobj))
(setq coords (list 
(list 1600.5625 396.3369) 
(list 1674.585 396.5869) 
(list 1674.585 396.7639) 
(list 1600.5625 396.4139)))
(apply 'command (append '("pline") coords '("c")))
(setq currobj (ssadd (entlast) currobj))
(setq coords (list 
(list 1600.5625 396.5569) 
(list 1674.585 396.9069) 
(list 1674.585 397.0839) 
(list 1600.5625 396.6339)))
(apply 'command (append '("pline") coords '("c")))
(setq currobj (ssadd (entlast) currobj))
(setq coords (list 
(list 1600.5625 396.7769) 
(list 1674.585 397.2269) 
(list 1674.585 397.4039) 
(list 1600.5625 396.8539)))
(apply 'command (append '("pline") coords '("c")))
(setq currobj (ssadd (entlast) currobj))
(setq coords (list 
(list 1600.5625 396.9969) 
(list 1674.585 397.5469) 
(list 1674.585 397.7239) 
(list 1600.5625 397.0739)))
(apply 'command (append '("pline") coords '("c")))
(setq currobj (ssadd (entlast) currobj))
(setq coords (list 
(list 1600.5625 397.2169) 
(list 1674.585 397.8669) 
(list 1674.585 398.0439) 
(list 1600.5625 397.2939)))
(apply 'command (append '("pline") coords '("c")))
(setq currobj (ssadd (entlast) currobj))
(setq coords (list 
(list 1599.4375 397.2939) 
(list 1525.415 398.0439) 
(list 1525.415 397.8669) 
(list 1599.4375 397.2169)))
(apply 'command (append '("pline") coords '("c")))
(setq currobj (ssadd (entlast) currobj))
(setq coords (list 
(list 1599.4375 397.0739) 
(list 1525.415 397.7239) 
(list 1525.415 397.5469) 
(list 1599.4375 396.9969)))
(apply 'command (append '("pline") coords '("c")))
(setq currobj (ssadd (entlast) currobj))
(setq coords (list 
(list 1599.4375 396.8539) 
(list 1525.415 397.4039) 
(list 1525.415 397.2269) 
(list 1599.4375 396.7769)))
(apply 'command (append '("pline") coords '("c")))
(setq currobj (ssadd (entlast) currobj))
(setq coords (list 
(list 1599.4375 396.6339) 
(list 1525.415 397.0839) 
(list 1525.415 396.9069) 
(list 1599.4375 396.5569)))
(apply 'command (append '("pline") coords '("c")))
(setq currobj (ssadd (entlast) currobj))
(setq coords (list 
(list 1599.4375 396.4139) 
(list 1525.415 396.7639) 
(list 1525.415 396.5869) 
(list 1599.4375 396.3369)))
(apply 'command (append '("pline") coords '("c")))
(setq currobj (ssadd (entlast) currobj))
(setq coords (list 
(list 1599.4375 396.1939) 
(list 1525.415 396.4439) 
(list 1525.415 396.2669) 
(list 1599.4375 396.1169)))
(apply 'command (append '("pline") coords '("c")))
(setq currobj (ssadd (entlast) currobj))
(setq coords (list 
(list 1599.4375 395.9739) 
(list 1525.415 396.1239) 
(list 1525.415 395.9469) 
(list 1599.4375 395.8969)))
(apply 'command (append '("pline") coords '("c")))
(setq currobj (ssadd (entlast) currobj))
(setq coords (list 
(list 1599.4375 395.7539) 
(list 1525.415 395.8039) 
(list 1525.415 395.6269) 
(list 1599.4375 395.6769)))
(apply 'command (append '("pline") coords '("c")))
(setq currobj (ssadd (entlast) currobj))
(setq coords (list 
(list 1599.4375 395.5339) 
(list 1525.415 395.4839) 
(list 1525.415 395.3069) 
(list 1599.4375 395.4569)))
(apply 'command (append '("pline") coords '("c")))
(setq currobj (ssadd (entlast) currobj))
(setq coords (list 
(list 1599.4375 395.3139) 
(list 1525.415 395.1639) 
(list 1525.415 394.9869) 
(list 1599.4375 395.2369)))
(apply 'command (append '("pline") coords '("c")))
(setq currobj (ssadd (entlast) currobj))
(setq coords (list 
(list 1599.4375 395.0939) 
(list 1525.415 394.8439) 
(list 1525.415 394.6669) 
(list 1599.4375 395.0169)))
(apply 'command (append '("pline") coords '("c")))
(setq currobj (ssadd (entlast) currobj))
(setq coords (list 
(list 1599.4375 394.8739) 
(list 1525.415 394.5239) 
(list 1525.415 394.3469) 
(list 1599.4375 394.7969)))
(apply 'command (append '("pline") coords '("c")))
(setq currobj (ssadd (entlast) currobj))
(setq coords (list 
(list 1599.4375 394.6539) 
(list 1525.415 394.2039) 
(list 1525.415 394.0269) 
(list 1599.4375 394.5769)))
(apply 'command (append '("pline") coords '("c")))
(setq currobj (ssadd (entlast) currobj))
(setq coords (list 
(list 1599.4375 394.4339) 
(list 1525.415 393.8839) 
(list 1525.415 393.7069) 
(list 1599.4375 394.3569)))
(apply 'command (append '("pline") coords '("c")))
(setq currobj (ssadd (entlast) currobj))
(setq coords (list 
(list 1599.4375 394.2139) 
(list 1525.415 393.5639) 
(list 1525.415 393.3869) 
(list 1599.4375 394.1369)))
(apply 'command (append '("pline") coords '("c")))
(setq currobj (ssadd (entlast) currobj))
(command "_layer" "set" "nitride" "")
(command "_layer" "set" "text" "")
(command "_circle" "1599.0625,382.9939" "0.075")
(command "_circle" "1599.0625,383.2939" "0.075")
(command "_circle" "1599.0625,383.5939" "0.075")
(command "_circle" "1599.0625,383.8939" "0.075")
(command "_circle" "1599.0625,384.1939" "0.075")
(command "_circle" "1598.7625,382.9939" "0.075")
(command "_circle" "1598.7625,383.2939" "0.075")
(command "_circle" "1598.7625,383.5939" "0.075")
(command "_circle" "1598.7625,383.8939" "0.075")
(command "_circle" "1598.7625,384.1939" "0.075")
(command "_circle" "1598.4625,382.9939" "0.075")
(command "_circle" "1598.4625,383.2939" "0.075")
(command "_circle" "1598.4625,383.5939" "0.075")
(command "_circle" "1598.4625,383.8939" "0.075")
(command "_circle" "1598.4625,384.1939" "0.075")
(command "_circle" "1598.1625,382.9939" "0.075")
(command "_circle" "1598.1625,383.2939" "0.075")
(command "_circle" "1598.1625,383.5939" "0.075")
(command "_circle" "1598.1625,383.8939" "0.075")
(command "_circle" "1598.1625,384.1939" "0.075")
(command "_circle" "1597.8625,382.9939" "0.075")
(command "_circle" "1597.8625,383.2939" "0.075")
(command "_circle" "1597.8625,383.5939" "0.075")
(command "_circle" "1597.8625,383.8939" "0.075")
(command "_circle" "1597.8625,384.1939" "0.075")
(command "_layer" "set" "nitride" "")
(setq coords (list 
(list 1600.2625 408.4369) 
(list 1600.2625 524.0816) 
(list 1599.7375 524.0816) 
(list 1599.7375 408.4369)))
(apply 'command (append '("pline") coords '("c")))
(setq currobj (ssadd (entlast) currobj))
(command "_layer" "set" "prebias" "")
(command "_rectangle" "1599.7375,408.4369" "1600.2625,524.0816")
(setq currobj (ssadd (entlast) currobj))
(command "_layer" "set" "nitride" "")
(setq coords (list 
(list 1600.2625 524.0816) 
(list 1600.5625 534.0816) 
(list 1600.5625 534.0816) 
(list 1600.5625 535.0816) 
(list 1674.585 534.3316) 
(list 1674.585 539.2746) 
(list 1600.5625 538.5246) 
(list 1600.5625 539.5246) 
(list 1600.5625 539.5246) 
(list 1600.2625 549.5246) 
(list 1599.7375 549.5246) 
(list 1599.4375 539.5246) 
(list 1599.4375 539.5246) 
(list 1599.4375 538.5246) 
(list 1525.415 539.2746) 
(list 1525.415 534.3316) 
(list 1599.4375 535.0816) 
(list 1599.4375 534.0816) 
(list 1599.4375 534.0816) 
(list 1599.7375 524.0816)))
(apply 'command (append '("pline") coords '("c")))
(setq currobj (ssadd (entlast) currobj))
(command "_layer" "set" "prebias" "")
(setq coords (list 
(list 1599.4375 524.0816) 
(list 1599.4375 535.0816) 
(list 1525.415 534.3316) 
(list 1525.415 539.2746) 
(list 1599.4375 538.5246) 
(list 1599.4375 549.5246) 
(list 1600.5625 549.5246) 
(list 1600.5625 538.5246) 
(list 1674.585 539.2746) 
(list 1674.585 534.3316) 
(list 1600.5625 535.0816) 
(list 1600.5625 524.0816)))
(apply 'command (append '("pline") coords '("c")))
(setq currobj (ssadd (entlast) currobj))
(command "_layer" "set" "nitride" "")
(command "_layer" "set" "fda1" "")
(setq coords (list 
(list 1600.5625 535.2246) 
(list 1674.585 534.4746) 
(list 1674.585 534.6516) 
(list 1600.5625 535.3016)))
(apply 'command (append '("pline") coords '("c")))
(setq currobj (ssadd (entlast) currobj))
(setq coords (list 
(list 1600.5625 535.4446) 
(list 1674.585 534.7946) 
(list 1674.585 534.9716) 
(list 1600.5625 535.5216)))
(apply 'command (append '("pline") coords '("c")))
(setq currobj (ssadd (entlast) currobj))
(setq coords (list 
(list 1600.5625 535.6646) 
(list 1674.585 535.1146) 
(list 1674.585 535.2916) 
(list 1600.5625 535.7416)))
(apply 'command (append '("pline") coords '("c")))
(setq currobj (ssadd (entlast) currobj))
(setq coords (list 
(list 1600.5625 535.8846) 
(list 1674.585 535.4346) 
(list 1674.585 535.6116) 
(list 1600.5625 535.9616)))
(apply 'command (append '("pline") coords '("c")))
(setq currobj (ssadd (entlast) currobj))
(setq coords (list 
(list 1600.5625 536.1046) 
(list 1674.585 535.7546) 
(list 1674.585 535.9316) 
(list 1600.5625 536.1816)))
(apply 'command (append '("pline") coords '("c")))
(setq currobj (ssadd (entlast) currobj))
(setq coords (list 
(list 1600.5625 536.3246) 
(list 1674.585 536.0746) 
(list 1674.585 536.2516) 
(list 1600.5625 536.4016)))
(apply 'command (append '("pline") coords '("c")))
(setq currobj (ssadd (entlast) currobj))
(setq coords (list 
(list 1600.5625 536.5446) 
(list 1674.585 536.3946) 
(list 1674.585 536.5716) 
(list 1600.5625 536.6216)))
(apply 'command (append '("pline") coords '("c")))
(setq currobj (ssadd (entlast) currobj))
(setq coords (list 
(list 1600.5625 536.7646) 
(list 1674.585 536.7146) 
(list 1674.585 536.8916) 
(list 1600.5625 536.8416)))
(apply 'command (append '("pline") coords '("c")))
(setq currobj (ssadd (entlast) currobj))
(setq coords (list 
(list 1600.5625 536.9846) 
(list 1674.585 537.0346) 
(list 1674.585 537.2116) 
(list 1600.5625 537.0616)))
(apply 'command (append '("pline") coords '("c")))
(setq currobj (ssadd (entlast) currobj))
(setq coords (list 
(list 1600.5625 537.2046) 
(list 1674.585 537.3546) 
(list 1674.585 537.5316) 
(list 1600.5625 537.2816)))
(apply 'command (append '("pline") coords '("c")))
(setq currobj (ssadd (entlast) currobj))
(setq coords (list 
(list 1600.5625 537.4246) 
(list 1674.585 537.6746) 
(list 1674.585 537.8516) 
(list 1600.5625 537.5016)))
(apply 'command (append '("pline") coords '("c")))
(setq currobj (ssadd (entlast) currobj))
(setq coords (list 
(list 1600.5625 537.6446) 
(list 1674.585 537.9946) 
(list 1674.585 538.1716) 
(list 1600.5625 537.7216)))
(apply 'command (append '("pline") coords '("c")))
(setq currobj (ssadd (entlast) currobj))
(setq coords (list 
(list 1600.5625 537.8646) 
(list 1674.585 538.3146) 
(list 1674.585 538.4916) 
(list 1600.5625 537.9416)))
(apply 'command (append '("pline") coords '("c")))
(setq currobj (ssadd (entlast) currobj))
(setq coords (list 
(list 1600.5625 538.0846) 
(list 1674.585 538.6346) 
(list 1674.585 538.8116) 
(list 1600.5625 538.1616)))
(apply 'command (append '("pline") coords '("c")))
(setq currobj (ssadd (entlast) currobj))
(setq coords (list 
(list 1600.5625 538.3046) 
(list 1674.585 538.9546) 
(list 1674.585 539.1316) 
(list 1600.5625 538.3816)))
(apply 'command (append '("pline") coords '("c")))
(setq currobj (ssadd (entlast) currobj))
(setq coords (list 
(list 1599.4375 538.3816) 
(list 1525.415 539.1316) 
(list 1525.415 538.9546) 
(list 1599.4375 538.3046)))
(apply 'command (append '("pline") coords '("c")))
(setq currobj (ssadd (entlast) currobj))
(setq coords (list 
(list 1599.4375 538.1616) 
(list 1525.415 538.8116) 
(list 1525.415 538.6346) 
(list 1599.4375 538.0846)))
(apply 'command (append '("pline") coords '("c")))
(setq currobj (ssadd (entlast) currobj))
(setq coords (list 
(list 1599.4375 537.9416) 
(list 1525.415 538.4916) 
(list 1525.415 538.3146) 
(list 1599.4375 537.8646)))
(apply 'command (append '("pline") coords '("c")))
(setq currobj (ssadd (entlast) currobj))
(setq coords (list 
(list 1599.4375 537.7216) 
(list 1525.415 538.1716) 
(list 1525.415 537.9946) 
(list 1599.4375 537.6446)))
(apply 'command (append '("pline") coords '("c")))
(setq currobj (ssadd (entlast) currobj))
(setq coords (list 
(list 1599.4375 537.5016) 
(list 1525.415 537.8516) 
(list 1525.415 537.6746) 
(list 1599.4375 537.4246)))
(apply 'command (append '("pline") coords '("c")))
(setq currobj (ssadd (entlast) currobj))
(setq coords (list 
(list 1599.4375 537.2816) 
(list 1525.415 537.5316) 
(list 1525.415 537.3546) 
(list 1599.4375 537.2046)))
(apply 'command (append '("pline") coords '("c")))
(setq currobj (ssadd (entlast) currobj))
(setq coords (list 
(list 1599.4375 537.0616) 
(list 1525.415 537.2116) 
(list 1525.415 537.0346) 
(list 1599.4375 536.9846)))
(apply 'command (append '("pline") coords '("c")))
(setq currobj (ssadd (entlast) currobj))
(setq coords (list 
(list 1599.4375 536.8416) 
(list 1525.415 536.8916) 
(list 1525.415 536.7146) 
(list 1599.4375 536.7646)))
(apply 'command (append '("pline") coords '("c")))
(setq currobj (ssadd (entlast) currobj))
(setq coords (list 
(list 1599.4375 536.6216) 
(list 1525.415 536.5716) 
(list 1525.415 536.3946) 
(list 1599.4375 536.5446)))
(apply 'command (append '("pline") coords '("c")))
(setq currobj (ssadd (entlast) currobj))
(setq coords (list 
(list 1599.4375 536.4016) 
(list 1525.415 536.2516) 
(list 1525.415 536.0746) 
(list 1599.4375 536.3246)))
(apply 'command (append '("pline") coords '("c")))
(setq currobj (ssadd (entlast) currobj))
(setq coords (list 
(list 1599.4375 536.1816) 
(list 1525.415 535.9316) 
(list 1525.415 535.7546) 
(list 1599.4375 536.1046)))
(apply 'command (append '("pline") coords '("c")))
(setq currobj (ssadd (entlast) currobj))
(setq coords (list 
(list 1599.4375 535.9616) 
(list 1525.415 535.6116) 
(list 1525.415 535.4346) 
(list 1599.4375 535.8846)))
(apply 'command (append '("pline") coords '("c")))
(setq currobj (ssadd (entlast) currobj))
(setq coords (list 
(list 1599.4375 535.7416) 
(list 1525.415 535.2916) 
(list 1525.415 535.1146) 
(list 1599.4375 535.6646)))
(apply 'command (append '("pline") coords '("c")))
(setq currobj (ssadd (entlast) currobj))
(setq coords (list 
(list 1599.4375 535.5216) 
(list 1525.415 534.9716) 
(list 1525.415 534.7946) 
(list 1599.4375 535.4446)))
(apply 'command (append '("pline") coords '("c")))
(setq currobj (ssadd (entlast) currobj))
(setq coords (list 
(list 1599.4375 535.3016) 
(list 1525.415 534.6516) 
(list 1525.415 534.4746) 
(list 1599.4375 535.2246)))
(apply 'command (append '("pline") coords '("c")))
(setq currobj (ssadd (entlast) currobj))
(command "_layer" "set" "nitride" "")
(command "_layer" "set" "text" "")
(command "_circle" "1599.0625,524.0816" "0.075")
(command "_circle" "1599.0625,524.3816" "0.075")
(command "_circle" "1599.0625,524.6816" "0.075")
(command "_circle" "1599.0625,524.9816" "0.075")
(command "_circle" "1599.0625,525.2816" "0.075")
(command "_circle" "1598.7625,524.0816" "0.075")
(command "_circle" "1598.7625,524.3816" "0.075")
(command "_circle" "1598.7625,524.6816" "0.075")
(command "_circle" "1598.7625,524.9816" "0.075")
(command "_circle" "1598.7625,525.2816" "0.075")
(command "_circle" "1598.4625,524.0816" "0.075")
(command "_circle" "1598.4625,524.3816" "0.075")
(command "_circle" "1598.4625,524.6816" "0.075")
(command "_circle" "1598.4625,524.9816" "0.075")
(command "_circle" "1598.4625,525.2816" "0.075")
(command "_circle" "1598.1625,524.0816" "0.075")
(command "_circle" "1598.1625,524.3816" "0.075")
(command "_circle" "1598.1625,524.6816" "0.075")
(command "_circle" "1598.1625,524.9816" "0.075")
(command "_circle" "1598.1625,525.2816" "0.075")
(command "_circle" "1597.8625,524.0816" "0.075")
(command "_circle" "1597.8625,524.3816" "0.075")
(command "_circle" "1597.8625,524.6816" "0.075")
(command "_circle" "1597.8625,524.9816" "0.075")
(command "_circle" "1597.8625,525.2816" "0.075")
(command "_layer" "set" "nitride" "")
(setq coords (list 
(list 1600.2625 549.5246) 
(list 1600.2625 665.1693) 
(list 1599.7375 665.1693) 
(list 1599.7375 549.5246)))
(apply 'command (append '("pline") coords '("c")))
(setq currobj (ssadd (entlast) currobj))
(command "_layer" "set" "prebias" "")
(command "_rectangle" "1599.7375,549.5246" "1600.2625,665.1693")
(setq currobj (ssadd (entlast) currobj))
(command "_layer" "set" "nitride" "")
(setq coords (list 
(list 1600.2625 665.1693) 
(list 1600.5625 675.1693) 
(list 1600.5625 675.1693) 
(list 1600.5625 676.1693) 
(list 1674.585 675.4193) 
(list 1674.585 680.3623) 
(list 1600.5625 679.6123) 
(list 1600.5625 680.6123) 
(list 1600.5625 680.6123) 
(list 1600.2625 690.6123) 
(list 1599.7375 690.6123) 
(list 1599.4375 680.6123) 
(list 1599.4375 680.6123) 
(list 1599.4375 679.6123) 
(list 1525.415 680.3623) 
(list 1525.415 675.4193) 
(list 1599.4375 676.1693) 
(list 1599.4375 675.1693) 
(list 1599.4375 675.1693) 
(list 1599.7375 665.1693)))
(apply 'command (append '("pline") coords '("c")))
(setq currobj (ssadd (entlast) currobj))
(command "_layer" "set" "prebias" "")
(setq coords (list 
(list 1599.4375 665.1693) 
(list 1599.4375 676.1693) 
(list 1525.415 675.4193) 
(list 1525.415 680.3623) 
(list 1599.4375 679.6123) 
(list 1599.4375 690.6123) 
(list 1600.5625 690.6123) 
(list 1600.5625 679.6123) 
(list 1674.585 680.3623) 
(list 1674.585 675.4193) 
(list 1600.5625 676.1693) 
(list 1600.5625 665.1693)))
(apply 'command (append '("pline") coords '("c")))
(setq currobj (ssadd (entlast) currobj))
(command "_layer" "set" "nitride" "")
(command "_layer" "set" "fda1" "")
(setq coords (list 
(list 1600.5625 676.3123) 
(list 1674.585 675.5623) 
(list 1674.585 675.7393) 
(list 1600.5625 676.3893)))
(apply 'command (append '("pline") coords '("c")))
(setq currobj (ssadd (entlast) currobj))
(setq coords (list 
(list 1600.5625 676.5323) 
(list 1674.585 675.8823) 
(list 1674.585 676.0593) 
(list 1600.5625 676.6093)))
(apply 'command (append '("pline") coords '("c")))
(setq currobj (ssadd (entlast) currobj))
(setq coords (list 
(list 1600.5625 676.7523) 
(list 1674.585 676.2023) 
(list 1674.585 676.3793) 
(list 1600.5625 676.8293)))
(apply 'command (append '("pline") coords '("c")))
(setq currobj (ssadd (entlast) currobj))
(setq coords (list 
(list 1600.5625 676.9723) 
(list 1674.585 676.5223) 
(list 1674.585 676.6993) 
(list 1600.5625 677.0493)))
(apply 'command (append '("pline") coords '("c")))
(setq currobj (ssadd (entlast) currobj))
(setq coords (list 
(list 1600.5625 677.1923) 
(list 1674.585 676.8423) 
(list 1674.585 677.0193) 
(list 1600.5625 677.2693)))
(apply 'command (append '("pline") coords '("c")))
(setq currobj (ssadd (entlast) currobj))
(setq coords (list 
(list 1600.5625 677.4123) 
(list 1674.585 677.1623) 
(list 1674.585 677.3393) 
(list 1600.5625 677.4893)))
(apply 'command (append '("pline") coords '("c")))
(setq currobj (ssadd (entlast) currobj))
(setq coords (list 
(list 1600.5625 677.6323) 
(list 1674.585 677.4823) 
(list 1674.585 677.6593) 
(list 1600.5625 677.7093)))
(apply 'command (append '("pline") coords '("c")))
(setq currobj (ssadd (entlast) currobj))
(setq coords (list 
(list 1600.5625 677.8523) 
(list 1674.585 677.8023) 
(list 1674.585 677.9793) 
(list 1600.5625 677.9293)))
(apply 'command (append '("pline") coords '("c")))
(setq currobj (ssadd (entlast) currobj))
(setq coords (list 
(list 1600.5625 678.0723) 
(list 1674.585 678.1223) 
(list 1674.585 678.2993) 
(list 1600.5625 678.1493)))
(apply 'command (append '("pline") coords '("c")))
(setq currobj (ssadd (entlast) currobj))
(setq coords (list 
(list 1600.5625 678.2923) 
(list 1674.585 678.4423) 
(list 1674.585 678.6193) 
(list 1600.5625 678.3693)))
(apply 'command (append '("pline") coords '("c")))
(setq currobj (ssadd (entlast) currobj))
(setq coords (list 
(list 1600.5625 678.5123) 
(list 1674.585 678.7623) 
(list 1674.585 678.9393) 
(list 1600.5625 678.5893)))
(apply 'command (append '("pline") coords '("c")))
(setq currobj (ssadd (entlast) currobj))
(setq coords (list 
(list 1600.5625 678.7323) 
(list 1674.585 679.0823) 
(list 1674.585 679.2593) 
(list 1600.5625 678.8093)))
(apply 'command (append '("pline") coords '("c")))
(setq currobj (ssadd (entlast) currobj))
(setq coords (list 
(list 1600.5625 678.9523) 
(list 1674.585 679.4023) 
(list 1674.585 679.5793) 
(list 1600.5625 679.0293)))
(apply 'command (append '("pline") coords '("c")))
(setq currobj (ssadd (entlast) currobj))
(setq coords (list 
(list 1600.5625 679.1723) 
(list 1674.585 679.7223) 
(list 1674.585 679.8993) 
(list 1600.5625 679.2493)))
(apply 'command (append '("pline") coords '("c")))
(setq currobj (ssadd (entlast) currobj))
(setq coords (list 
(list 1600.5625 679.3923) 
(list 1674.585 680.0423) 
(list 1674.585 680.2193) 
(list 1600.5625 679.4693)))
(apply 'command (append '("pline") coords '("c")))
(setq currobj (ssadd (entlast) currobj))
(setq coords (list 
(list 1599.4375 679.4693) 
(list 1525.415 680.2193) 
(list 1525.415 680.0423) 
(list 1599.4375 679.3923)))
(apply 'command (append '("pline") coords '("c")))
(setq currobj (ssadd (entlast) currobj))
(setq coords (list 
(list 1599.4375 679.2493) 
(list 1525.415 679.8993) 
(list 1525.415 679.7223) 
(list 1599.4375 679.1723)))
(apply 'command (append '("pline") coords '("c")))
(setq currobj (ssadd (entlast) currobj))
(setq coords (list 
(list 1599.4375 679.0293) 
(list 1525.415 679.5793) 
(list 1525.415 679.4023) 
(list 1599.4375 678.9523)))
(apply 'command (append '("pline") coords '("c")))
(setq currobj (ssadd (entlast) currobj))
(setq coords (list 
(list 1599.4375 678.8093) 
(list 1525.415 679.2593) 
(list 1525.415 679.0823) 
(list 1599.4375 678.7323)))
(apply 'command (append '("pline") coords '("c")))
(setq currobj (ssadd (entlast) currobj))
(setq coords (list 
(list 1599.4375 678.5893) 
(list 1525.415 678.9393) 
(list 1525.415 678.7623) 
(list 1599.4375 678.5123)))
(apply 'command (append '("pline") coords '("c")))
(setq currobj (ssadd (entlast) currobj))
(setq coords (list 
(list 1599.4375 678.3693) 
(list 1525.415 678.6193) 
(list 1525.415 678.4423) 
(list 1599.4375 678.2923)))
(apply 'command (append '("pline") coords '("c")))
(setq currobj (ssadd (entlast) currobj))
(setq coords (list 
(list 1599.4375 678.1493) 
(list 1525.415 678.2993) 
(list 1525.415 678.1223) 
(list 1599.4375 678.0723)))
(apply 'command (append '("pline") coords '("c")))
(setq currobj (ssadd (entlast) currobj))
(setq coords (list 
(list 1599.4375 677.9293) 
(list 1525.415 677.9793) 
(list 1525.415 677.8023) 
(list 1599.4375 677.8523)))
(apply 'command (append '("pline") coords '("c")))
(setq currobj (ssadd (entlast) currobj))
(setq coords (list 
(list 1599.4375 677.7093) 
(list 1525.415 677.6593) 
(list 1525.415 677.4823) 
(list 1599.4375 677.6323)))
(apply 'command (append '("pline") coords '("c")))
(setq currobj (ssadd (entlast) currobj))
(setq coords (list 
(list 1599.4375 677.4893) 
(list 1525.415 677.3393) 
(list 1525.415 677.1623) 
(list 1599.4375 677.4123)))
(apply 'command (append '("pline") coords '("c")))
(setq currobj (ssadd (entlast) currobj))
(setq coords (list 
(list 1599.4375 677.2693) 
(list 1525.415 677.0193) 
(list 1525.415 676.8423) 
(list 1599.4375 677.1923)))
(apply 'command (append '("pline") coords '("c")))
(setq currobj (ssadd (entlast) currobj))
(setq coords (list 
(list 1599.4375 677.0493) 
(list 1525.415 676.6993) 
(list 1525.415 676.5223) 
(list 1599.4375 676.9723)))
(apply 'command (append '("pline") coords '("c")))
(setq currobj (ssadd (entlast) currobj))
(setq coords (list 
(list 1599.4375 676.8293) 
(list 1525.415 676.3793) 
(list 1525.415 676.2023) 
(list 1599.4375 676.7523)))
(apply 'command (append '("pline") coords '("c")))
(setq currobj (ssadd (entlast) currobj))
(setq coords (list 
(list 1599.4375 676.6093) 
(list 1525.415 676.0593) 
(list 1525.415 675.8823) 
(list 1599.4375 676.5323)))
(apply 'command (append '("pline") coords '("c")))
(setq currobj (ssadd (entlast) currobj))
(setq coords (list 
(list 1599.4375 676.3893) 
(list 1525.415 675.7393) 
(list 1525.415 675.5623) 
(list 1599.4375 676.3123)))
(apply 'command (append '("pline") coords '("c")))
(setq currobj (ssadd (entlast) currobj))
(command "_layer" "set" "nitride" "")
(command "_layer" "set" "text" "")
(command "_circle" "1599.0625,665.1693" "0.075")
(command "_circle" "1599.0625,665.4693" "0.075")
(command "_circle" "1599.0625,665.7693" "0.075")
(command "_circle" "1599.0625,666.0693" "0.075")
(command "_circle" "1599.0625,666.3693" "0.075")
(command "_circle" "1598.7625,665.1693" "0.075")
(command "_circle" "1598.7625,665.4693" "0.075")
(command "_circle" "1598.7625,665.7693" "0.075")
(command "_circle" "1598.7625,666.0693" "0.075")
(command "_circle" "1598.7625,666.3693" "0.075")
(command "_circle" "1598.4625,665.1693" "0.075")
(command "_circle" "1598.4625,665.4693" "0.075")
(command "_circle" "1598.4625,665.7693" "0.075")
(command "_circle" "1598.4625,666.0693" "0.075")
(command "_circle" "1598.4625,666.3693" "0.075")
(command "_circle" "1598.1625,665.1693" "0.075")
(command "_circle" "1598.1625,665.4693" "0.075")
(command "_circle" "1598.1625,665.7693" "0.075")
(command "_circle" "1598.1625,666.0693" "0.075")
(command "_circle" "1598.1625,666.3693" "0.075")
(command "_circle" "1597.8625,665.1693" "0.075")
(command "_circle" "1597.8625,665.4693" "0.075")
(command "_circle" "1597.8625,665.7693" "0.075")
(command "_circle" "1597.8625,666.0693" "0.075")
(command "_circle" "1597.8625,666.3693" "0.075")
(command "_layer" "set" "nitride" "")
(setq coords (list 
(list 1600.2625 690.6123) 
(list 1600.2625 806.257) 
(list 1599.7375 806.257) 
(list 1599.7375 690.6123)))
(apply 'command (append '("pline") coords '("c")))
(setq currobj (ssadd (entlast) currobj))
(command "_layer" "set" "prebias" "")
(command "_rectangle" "1599.7375,690.6123" "1600.2625,806.257")
(setq currobj (ssadd (entlast) currobj))
(command "_layer" "set" "nitride" "")
(setq coords (list 
(list 1600.2625 806.257) 
(list 1600.5625 816.257) 
(list 1600.5625 816.257) 
(list 1600.5625 817.257) 
(list 1674.585 816.507) 
(list 1674.585 821.45) 
(list 1600.5625 820.7) 
(list 1600.5625 821.7) 
(list 1600.5625 821.7) 
(list 1600.2625 831.7) 
(list 1599.7375 831.7) 
(list 1599.4375 821.7) 
(list 1599.4375 821.7) 
(list 1599.4375 820.7) 
(list 1525.415 821.45) 
(list 1525.415 816.507) 
(list 1599.4375 817.257) 
(list 1599.4375 816.257) 
(list 1599.4375 816.257) 
(list 1599.7375 806.257)))
(apply 'command (append '("pline") coords '("c")))
(setq currobj (ssadd (entlast) currobj))
(command "_layer" "set" "prebias" "")
(setq coords (list 
(list 1599.4375 806.257) 
(list 1599.4375 817.257) 
(list 1525.415 816.507) 
(list 1525.415 821.45) 
(list 1599.4375 820.7) 
(list 1599.4375 831.7) 
(list 1600.5625 831.7) 
(list 1600.5625 820.7) 
(list 1674.585 821.45) 
(list 1674.585 816.507) 
(list 1600.5625 817.257) 
(list 1600.5625 806.257)))
(apply 'command (append '("pline") coords '("c")))
(setq currobj (ssadd (entlast) currobj))
(command "_layer" "set" "nitride" "")
(command "_layer" "set" "fda1" "")
(setq coords (list 
(list 1600.5625 817.4) 
(list 1674.585 816.65) 
(list 1674.585 816.827) 
(list 1600.5625 817.477)))
(apply 'command (append '("pline") coords '("c")))
(setq currobj (ssadd (entlast) currobj))
(setq coords (list 
(list 1600.5625 817.62) 
(list 1674.585 816.97) 
(list 1674.585 817.147) 
(list 1600.5625 817.697)))
(apply 'command (append '("pline") coords '("c")))
(setq currobj (ssadd (entlast) currobj))
(setq coords (list 
(list 1600.5625 817.84) 
(list 1674.585 817.29) 
(list 1674.585 817.467) 
(list 1600.5625 817.917)))
(apply 'command (append '("pline") coords '("c")))
(setq currobj (ssadd (entlast) currobj))
(setq coords (list 
(list 1600.5625 818.06) 
(list 1674.585 817.61) 
(list 1674.585 817.787) 
(list 1600.5625 818.137)))
(apply 'command (append '("pline") coords '("c")))
(setq currobj (ssadd (entlast) currobj))
(setq coords (list 
(list 1600.5625 818.28) 
(list 1674.585 817.93) 
(list 1674.585 818.107) 
(list 1600.5625 818.357)))
(apply 'command (append '("pline") coords '("c")))
(setq currobj (ssadd (entlast) currobj))
(setq coords (list 
(list 1600.5625 818.5) 
(list 1674.585 818.25) 
(list 1674.585 818.427) 
(list 1600.5625 818.577)))
(apply 'command (append '("pline") coords '("c")))
(setq currobj (ssadd (entlast) currobj))
(setq coords (list 
(list 1600.5625 818.72) 
(list 1674.585 818.57) 
(list 1674.585 818.747) 
(list 1600.5625 818.797)))
(apply 'command (append '("pline") coords '("c")))
(setq currobj (ssadd (entlast) currobj))
(setq coords (list 
(list 1600.5625 818.94) 
(list 1674.585 818.89) 
(list 1674.585 819.067) 
(list 1600.5625 819.017)))
(apply 'command (append '("pline") coords '("c")))
(setq currobj (ssadd (entlast) currobj))
(setq coords (list 
(list 1600.5625 819.16) 
(list 1674.585 819.21) 
(list 1674.585 819.387) 
(list 1600.5625 819.237)))
(apply 'command (append '("pline") coords '("c")))
(setq currobj (ssadd (entlast) currobj))
(setq coords (list 
(list 1600.5625 819.38) 
(list 1674.585 819.53) 
(list 1674.585 819.707) 
(list 1600.5625 819.457)))
(apply 'command (append '("pline") coords '("c")))
(setq currobj (ssadd (entlast) currobj))
(setq coords (list 
(list 1600.5625 819.6) 
(list 1674.585 819.85) 
(list 1674.585 820.027) 
(list 1600.5625 819.677)))
(apply 'command (append '("pline") coords '("c")))
(setq currobj (ssadd (entlast) currobj))
(setq coords (list 
(list 1600.5625 819.82) 
(list 1674.585 820.17) 
(list 1674.585 820.347) 
(list 1600.5625 819.897)))
(apply 'command (append '("pline") coords '("c")))
(setq currobj (ssadd (entlast) currobj))
(setq coords (list 
(list 1600.5625 820.04) 
(list 1674.585 820.49) 
(list 1674.585 820.667) 
(list 1600.5625 820.117)))
(apply 'command (append '("pline") coords '("c")))
(setq currobj (ssadd (entlast) currobj))
(setq coords (list 
(list 1600.5625 820.26) 
(list 1674.585 820.81) 
(list 1674.585 820.987) 
(list 1600.5625 820.337)))
(apply 'command (append '("pline") coords '("c")))
(setq currobj (ssadd (entlast) currobj))
(setq coords (list 
(list 1600.5625 820.48) 
(list 1674.585 821.13) 
(list 1674.585 821.307) 
(list 1600.5625 820.557)))
(apply 'command (append '("pline") coords '("c")))
(setq currobj (ssadd (entlast) currobj))
(setq coords (list 
(list 1599.4375 820.557) 
(list 1525.415 821.307) 
(list 1525.415 821.13) 
(list 1599.4375 820.48)))
(apply 'command (append '("pline") coords '("c")))
(setq currobj (ssadd (entlast) currobj))
(setq coords (list 
(list 1599.4375 820.337) 
(list 1525.415 820.987) 
(list 1525.415 820.81) 
(list 1599.4375 820.26)))
(apply 'command (append '("pline") coords '("c")))
(setq currobj (ssadd (entlast) currobj))
(setq coords (list 
(list 1599.4375 820.117) 
(list 1525.415 820.667) 
(list 1525.415 820.49) 
(list 1599.4375 820.04)))
(apply 'command (append '("pline") coords '("c")))
(setq currobj (ssadd (entlast) currobj))
(setq coords (list 
(list 1599.4375 819.897) 
(list 1525.415 820.347) 
(list 1525.415 820.17) 
(list 1599.4375 819.82)))
(apply 'command (append '("pline") coords '("c")))
(setq currobj (ssadd (entlast) currobj))
(setq coords (list 
(list 1599.4375 819.677) 
(list 1525.415 820.027) 
(list 1525.415 819.85) 
(list 1599.4375 819.6)))
(apply 'command (append '("pline") coords '("c")))
(setq currobj (ssadd (entlast) currobj))
(setq coords (list 
(list 1599.4375 819.457) 
(list 1525.415 819.707) 
(list 1525.415 819.53) 
(list 1599.4375 819.38)))
(apply 'command (append '("pline") coords '("c")))
(setq currobj (ssadd (entlast) currobj))
(setq coords (list 
(list 1599.4375 819.237) 
(list 1525.415 819.387) 
(list 1525.415 819.21) 
(list 1599.4375 819.16)))
(apply 'command (append '("pline") coords '("c")))
(setq currobj (ssadd (entlast) currobj))
(setq coords (list 
(list 1599.4375 819.017) 
(list 1525.415 819.067) 
(list 1525.415 818.89) 
(list 1599.4375 818.94)))
(apply 'command (append '("pline") coords '("c")))
(setq currobj (ssadd (entlast) currobj))
(setq coords (list 
(list 1599.4375 818.797) 
(list 1525.415 818.747) 
(list 1525.415 818.57) 
(list 1599.4375 818.72)))
(apply 'command (append '("pline") coords '("c")))
(setq currobj (ssadd (entlast) currobj))
(setq coords (list 
(list 1599.4375 818.577) 
(list 1525.415 818.427) 
(list 1525.415 818.25) 
(list 1599.4375 818.5)))
(apply 'command (append '("pline") coords '("c")))
(setq currobj (ssadd (entlast) currobj))
(setq coords (list 
(list 1599.4375 818.357) 
(list 1525.415 818.107) 
(list 1525.415 817.93) 
(list 1599.4375 818.28)))
(apply 'command (append '("pline") coords '("c")))
(setq currobj (ssadd (entlast) currobj))
(setq coords (list 
(list 1599.4375 818.137) 
(list 1525.415 817.787) 
(list 1525.415 817.61) 
(list 1599.4375 818.06)))
(apply 'command (append '("pline") coords '("c")))
(setq currobj (ssadd (entlast) currobj))
(setq coords (list 
(list 1599.4375 817.917) 
(list 1525.415 817.467) 
(list 1525.415 817.29) 
(list 1599.4375 817.84)))
(apply 'command (append '("pline") coords '("c")))
(setq currobj (ssadd (entlast) currobj))
(setq coords (list 
(list 1599.4375 817.697) 
(list 1525.415 817.147) 
(list 1525.415 816.97) 
(list 1599.4375 817.62)))
(apply 'command (append '("pline") coords '("c")))
(setq currobj (ssadd (entlast) currobj))
(setq coords (list 
(list 1599.4375 817.477) 
(list 1525.415 816.827) 
(list 1525.415 816.65) 
(list 1599.4375 817.4)))
(apply 'command (append '("pline") coords '("c")))
(setq currobj (ssadd (entlast) currobj))
(command "_layer" "set" "nitride" "")
(command "_layer" "set" "text" "")
(command "_circle" "1599.0625,806.257" "0.075")
(command "_circle" "1599.0625,806.557" "0.075")
(command "_circle" "1599.0625,806.857" "0.075")
(command "_circle" "1599.0625,807.157" "0.075")
(command "_circle" "1599.0625,807.457" "0.075")
(command "_circle" "1598.7625,806.257" "0.075")
(command "_circle" "1598.7625,806.557" "0.075")
(command "_circle" "1598.7625,806.857" "0.075")
(command "_circle" "1598.7625,807.157" "0.075")
(command "_circle" "1598.7625,807.457" "0.075")
(command "_circle" "1598.4625,806.257" "0.075")
(command "_circle" "1598.4625,806.557" "0.075")
(command "_circle" "1598.4625,806.857" "0.075")
(command "_circle" "1598.4625,807.157" "0.075")
(command "_circle" "1598.4625,807.457" "0.075")
(command "_circle" "1598.1625,806.257" "0.075")
(command "_circle" "1598.1625,806.557" "0.075")
(command "_circle" "1598.1625,806.857" "0.075")
(command "_circle" "1598.1625,807.157" "0.075")
(command "_circle" "1598.1625,807.457" "0.075")
(command "_circle" "1597.8625,806.257" "0.075")
(command "_circle" "1597.8625,806.557" "0.075")
(command "_circle" "1597.8625,806.857" "0.075")
(command "_circle" "1597.8625,807.157" "0.075")
(command "_circle" "1597.8625,807.457" "0.075")
(command "_layer" "set" "nitride" "")
(setq coords (list 
(list 1600.2625 831.7) 
(list 1600.2625 836.7) 
(list 1599.7375 836.7) 
(list 1599.7375 831.7)))
(apply 'command (append '("pline") coords '("c")))
(setq currobj (ssadd (entlast) currobj))
(command "_layer" "set" "prebias" "")
(command "_rectangle" "1599.7375,831.7" "1600.2625,836.7")
(setq currobj (ssadd (entlast) currobj))
(command "_layer" "set" "nitride" "")
(setq cooledsinglenanobeam5 currobj)
(setq currobj nil)
(setq currobj (ssadd))
; DRAWING PHOTONIC CRYSTAL
(command "_layer" "set" "negYjunc" "")
(setq coords (list 
(list 1600.125 866.7) 
(list 1600 851.7) 
(list 1600 866.7)))
(apply 'command (append '("pline") coords '("c")))
(setq currobj (ssadd (entlast) currobj))
(setq coords (list 
(list 1600.2625 836.7) 
(list 1600.405 866.7) 
(list 1601.092 866.7) 
(list 1601.092 836.7)))
(apply 'command (append '("pline") coords '("c")))
(setq currobj (ssadd (entlast) currobj))
(setq coords (list 
(list 1599.875 866.7) 
(list 1600 851.7) 
(list 1600 866.7)))
(apply 'command (append '("pline") coords '("c")))
(setq currobj (ssadd (entlast) currobj))
(setq coords (list 
(list 1599.7375 836.7) 
(list 1599.595 866.7) 
(list 1598.908 866.7) 
(list 1598.908 836.7)))
(apply 'command (append '("pline") coords '("c")))
(setq currobj (ssadd (entlast) currobj))
(command "_layer" "set" "nitride" "")
(setq yjunction5 currobj)
(setq currobj nil)
(setq currobj (ssadd))
(setq tap5 nil)
(setq tap5 (ssadd))
(command "_layer" "set" "phc" "")
(setq coords (list 
(list 1600 866.7) 
(list 1600.125 866.7) 
(list 1600.125 866.7103) 
(list 1600.125 866.7206) 
(list 1600.125 866.7308) 
(list 1600.125 866.7411) 
(list 1600.125 866.7514) 
(list 1600.125 866.7617) 
(list 1600.125 866.7719) 
(list 1600.125 866.7822) 
(list 1600.125 866.7925) 
(list 1600.125 866.8028) 
(list 1600.125 866.8131) 
(list 1600.125 866.8233) 
(list 1600.125 866.8336) 
(list 1600.125 866.8439) 
(list 1600.125 866.8542) 
(list 1600.125 866.8644) 
(list 1600.125 866.8747) 
(list 1600.125 866.885) 
(list 1600.125 866.8953) 
(list 1600.125 866.9056) 
(list 1600.125 866.9158) 
(list 1600.125 866.9261) 
(list 1600.125 866.9364) 
(list 1600.125 866.9467) 
(list 1600.125 866.9569) 
(list 1600.125 866.9672) 
(list 1600.125 866.9775) 
(list 1600.125 866.9878) 
(list 1600.125 866.9981) 
(list 1600.125 867.0083) 
(list 1600.125 867.0186) 
(list 1600.125 867.0289) 
(list 1600.125 867.0392) 
(list 1600.125 867.0494) 
(list 1600.125 867.0597) 
(list 1600.125 867.07) 
(list 1600 867.07)))
(apply 'command (append '("pline") coords '("c")))
(setq tap5 (ssadd (entlast) tap5))
(command "_mirror" (entlast) "" "1600,900" "1600,901" "No")
(setq tap5 (ssadd (entlast) tap5))
(setq coords (list 
(list 1600.4144 866.7) 
(list 1600.405 866.7) 
(list 1600.4053 866.7103) 
(list 1600.4055 866.7206) 
(list 1600.4057 866.7308) 
(list 1600.4058 866.7411) 
(list 1600.4059 866.7514) 
(list 1600.4059 866.7617) 
(list 1600.4057 866.7719) 
(list 1600.4055 866.7822) 
(list 1600.4052 866.7925) 
(list 1600.4049 866.8028) 
(list 1600.4044 866.8131) 
(list 1600.4039 866.8233) 
(list 1600.4034 866.8336) 
(list 1600.4028 866.8439) 
(list 1600.4023 866.8542) 
(list 1600.4019 866.8644) 
(list 1600.4015 866.8747) 
(list 1600.4012 866.885) 
(list 1600.4011 866.8953) 
(list 1600.4011 866.9056) 
(list 1600.4013 866.9158) 
(list 1600.4016 866.9261) 
(list 1600.4021 866.9364) 
(list 1600.4028 866.9467) 
(list 1600.4036 866.9569) 
(list 1600.4046 866.9672) 
(list 1600.4057 866.9775) 
(list 1600.4069 866.9878) 
(list 1600.4081 866.9981) 
(list 1600.4093 867.0083) 
(list 1600.4105 867.0186) 
(list 1600.4116 867.0289) 
(list 1600.4126 867.0392) 
(list 1600.4134 867.0494) 
(list 1600.414 867.0597) 
(list 1600.4144 867.07) 
(list 1600.4144 867.07)))
(apply 'command (append '("pline") coords '("c")))
(setq tap5 (ssadd (entlast) tap5))
(command "_mirror" (entlast) "" "1600,900" "1600,901" "No")
(setq tap5 (ssadd (entlast) tap5))
(setq coords (list 
(list 1601.092 866.7) 
(list 1600.4144 866.7) 
(list 1600.4144 866.7103) 
(list 1600.4144 866.7206) 
(list 1600.4144 866.7308) 
(list 1600.4144 866.7411) 
(list 1600.4144 866.7514) 
(list 1600.4144 866.7617) 
(list 1600.4144 866.7719) 
(list 1600.4144 866.7822) 
(list 1600.4144 866.7925) 
(list 1600.4144 866.8028) 
(list 1600.4144 866.8131) 
(list 1600.4144 866.8233) 
(list 1600.4144 866.8336) 
(list 1600.4144 866.8439) 
(list 1600.4144 866.8542) 
(list 1600.4144 866.8644) 
(list 1600.4144 866.8747) 
(list 1600.4144 866.885) 
(list 1600.4144 866.8953) 
(list 1600.4144 866.9056) 
(list 1600.4144 866.9158) 
(list 1600.4144 866.9261) 
(list 1600.4144 866.9364) 
(list 1600.4144 866.9467) 
(list 1600.4144 866.9569) 
(list 1600.4144 866.9672) 
(list 1600.4144 866.9775) 
(list 1600.4144 866.9878) 
(list 1600.4144 866.9981) 
(list 1600.4144 867.0083) 
(list 1600.4144 867.0186) 
(list 1600.4144 867.0289) 
(list 1600.4144 867.0392) 
(list 1600.4144 867.0494) 
(list 1600.4144 867.0597) 
(list 1600.4144 867.07) 
(list 1601.092 867.07)))
(apply 'command (append '("pline") coords '("c")))
(setq tap5 (ssadd (entlast) tap5))
(command "_mirror" (entlast) "" "1600,900" "1600,901" "No")
(setq tap5 (ssadd (entlast) tap5))
(setq coords (list 
(list 1600 867.07) 
(list 1600.125 867.07) 
(list 1600.125 867.0803) 
(list 1600.125 867.0906) 
(list 1600.125 867.1008) 
(list 1600.125 867.1111) 
(list 1600.125 867.1214) 
(list 1600.125 867.1317) 
(list 1600.125 867.1419) 
(list 1600.125 867.1522) 
(list 1600.125 867.1625) 
(list 1600.125 867.1728) 
(list 1600.125 867.1831) 
(list 1600.125 867.1933) 
(list 1600.125 867.2036) 
(list 1600.125 867.2139) 
(list 1600.125 867.2242) 
(list 1600.125 867.2344) 
(list 1600.125 867.2447) 
(list 1600.125 867.255) 
(list 1600.125 867.2653) 
(list 1600.125 867.2756) 
(list 1600.125 867.2858) 
(list 1600.125 867.2961) 
(list 1600.125 867.3064) 
(list 1600.125 867.3167) 
(list 1600.125 867.3269) 
(list 1600.125 867.3372) 
(list 1600.125 867.3475) 
(list 1600.125 867.3578) 
(list 1600.125 867.3681) 
(list 1600.125 867.3783) 
(list 1600.125 867.3886) 
(list 1600.125 867.3989) 
(list 1600.125 867.4092) 
(list 1600.125 867.4194) 
(list 1600.125 867.4297) 
(list 1600.125 867.44) 
(list 1600 867.44)))
(apply 'command (append '("pline") coords '("c")))
(setq tap5 (ssadd (entlast) tap5))
(command "_mirror" (entlast) "" "1600,900" "1600,901" "No")
(setq tap5 (ssadd (entlast) tap5))
(setq coords (list 
(list 1600.4238 867.07) 
(list 1600.4144 867.07) 
(list 1600.4145 867.0803) 
(list 1600.4144 867.0906) 
(list 1600.414 867.1008) 
(list 1600.4132 867.1111) 
(list 1600.4123 867.1214) 
(list 1600.411 867.1317) 
(list 1600.4096 867.1419) 
(list 1600.4079 867.1522) 
(list 1600.4062 867.1625) 
(list 1600.4043 867.1728) 
(list 1600.4024 867.1831) 
(list 1600.4006 867.1933) 
(list 1600.3989 867.2036) 
(list 1600.3973 867.2139) 
(list 1600.3959 867.2242) 
(list 1600.3949 867.2344) 
(list 1600.3941 867.2447) 
(list 1600.3937 867.255) 
(list 1600.3937 867.2653) 
(list 1600.3941 867.2756) 
(list 1600.3949 867.2858) 
(list 1600.3961 867.2961) 
(list 1600.3976 867.3064) 
(list 1600.3995 867.3167) 
(list 1600.4017 867.3269) 
(list 1600.4041 867.3372) 
(list 1600.4066 867.3475) 
(list 1600.4093 867.3578) 
(list 1600.4119 867.3681) 
(list 1600.4145 867.3783) 
(list 1600.4169 867.3886) 
(list 1600.419 867.3989) 
(list 1600.4208 867.4092) 
(list 1600.4223 867.4194) 
(list 1600.4233 867.4297) 
(list 1600.4238 867.44) 
(list 1600.4238 867.44)))
(apply 'command (append '("pline") coords '("c")))
(setq tap5 (ssadd (entlast) tap5))
(command "_mirror" (entlast) "" "1600,900" "1600,901" "No")
(setq tap5 (ssadd (entlast) tap5))
(setq coords (list 
(list 1601.092 867.07) 
(list 1600.4238 867.07) 
(list 1600.4238 867.0803) 
(list 1600.4238 867.0906) 
(list 1600.4238 867.1008) 
(list 1600.4238 867.1111) 
(list 1600.4238 867.1214) 
(list 1600.4238 867.1317) 
(list 1600.4238 867.1419) 
(list 1600.4238 867.1522) 
(list 1600.4238 867.1625) 
(list 1600.4238 867.1728) 
(list 1600.4238 867.1831) 
(list 1600.4238 867.1933) 
(list 1600.4238 867.2036) 
(list 1600.4238 867.2139) 
(list 1600.4238 867.2242) 
(list 1600.4238 867.2344) 
(list 1600.4238 867.2447) 
(list 1600.4238 867.255) 
(list 1600.4238 867.2653) 
(list 1600.4238 867.2756) 
(list 1600.4238 867.2858) 
(list 1600.4238 867.2961) 
(list 1600.4238 867.3064) 
(list 1600.4238 867.3167) 
(list 1600.4238 867.3269) 
(list 1600.4238 867.3372) 
(list 1600.4238 867.3475) 
(list 1600.4238 867.3578) 
(list 1600.4238 867.3681) 
(list 1600.4238 867.3783) 
(list 1600.4238 867.3886) 
(list 1600.4238 867.3989) 
(list 1600.4238 867.4092) 
(list 1600.4238 867.4194) 
(list 1600.4238 867.4297) 
(list 1600.4238 867.44) 
(list 1601.092 867.44)))
(apply 'command (append '("pline") coords '("c")))
(setq tap5 (ssadd (entlast) tap5))
(command "_mirror" (entlast) "" "1600,900" "1600,901" "No")
(setq tap5 (ssadd (entlast) tap5))
(setq coords (list 
(list 1600 867.44) 
(list 1600.125 867.44) 
(list 1600.125 867.4503) 
(list 1600.125 867.4606) 
(list 1600.125 867.4708) 
(list 1600.125 867.4811) 
(list 1600.125 867.4914) 
(list 1600.125 867.5017) 
(list 1600.125 867.5119) 
(list 1600.125 867.5222) 
(list 1600.125 867.5325) 
(list 1600.125 867.5428) 
(list 1600.125 867.5531) 
(list 1600.125 867.5633) 
(list 1600.125 867.5736) 
(list 1600.125 867.5839) 
(list 1600.125 867.5942) 
(list 1600.125 867.6044) 
(list 1600.125 867.6147) 
(list 1600.125 867.625) 
(list 1600.125 867.6353) 
(list 1600.125 867.6456) 
(list 1600.125 867.6558) 
(list 1600.125 867.6661) 
(list 1600.125 867.6764) 
(list 1600.125 867.6867) 
(list 1600.125 867.6969) 
(list 1600.125 867.7072) 
(list 1600.125 867.7175) 
(list 1600.125 867.7278) 
(list 1600.125 867.7381) 
(list 1600.125 867.7483) 
(list 1600.125 867.7586) 
(list 1600.125 867.7689) 
(list 1600.125 867.7792) 
(list 1600.125 867.7894) 
(list 1600.125 867.7997) 
(list 1600.125 867.81) 
(list 1600 867.81)))
(apply 'command (append '("pline") coords '("c")))
(setq tap5 (ssadd (entlast) tap5))
(command "_mirror" (entlast) "" "1600,900" "1600,901" "No")
(setq tap5 (ssadd (entlast) tap5))
(setq coords (list 
(list 1600.4332 867.44) 
(list 1600.4238 867.44) 
(list 1600.4238 867.4503) 
(list 1600.4233 867.4606) 
(list 1600.4222 867.4708) 
(list 1600.4207 867.4811) 
(list 1600.4186 867.4914) 
(list 1600.4162 867.5017) 
(list 1600.4134 867.5119) 
(list 1600.4103 867.5222) 
(list 1600.4071 867.5325) 
(list 1600.4038 867.5428) 
(list 1600.4005 867.5531) 
(list 1600.3973 867.5633) 
(list 1600.3944 867.5736) 
(list 1600.3917 867.5839) 
(list 1600.3895 867.5942) 
(list 1600.3878 867.6044) 
(list 1600.3867 867.6147) 
(list 1600.3862 867.625) 
(list 1600.3863 867.6353) 
(list 1600.3871 867.6456) 
(list 1600.3885 867.6558) 
(list 1600.3905 867.6661) 
(list 1600.3931 867.6764) 
(list 1600.3962 867.6867) 
(list 1600.3997 867.6969) 
(list 1600.4035 867.7072) 
(list 1600.4076 867.7175) 
(list 1600.4117 867.7278) 
(list 1600.4157 867.7381) 
(list 1600.4196 867.7483) 
(list 1600.4232 867.7586) 
(list 1600.4264 867.7689) 
(list 1600.4291 867.7792) 
(list 1600.4312 867.7894) 
(list 1600.4326 867.7997) 
(list 1600.4332 867.81) 
(list 1600.4332 867.81)))
(apply 'command (append '("pline") coords '("c")))
(setq tap5 (ssadd (entlast) tap5))
(command "_mirror" (entlast) "" "1600,900" "1600,901" "No")
(setq tap5 (ssadd (entlast) tap5))
(setq coords (list 
(list 1601.092 867.44) 
(list 1600.4332 867.44) 
(list 1600.4332 867.4503) 
(list 1600.4332 867.4606) 
(list 1600.4332 867.4708) 
(list 1600.4332 867.4811) 
(list 1600.4332 867.4914) 
(list 1600.4332 867.5017) 
(list 1600.4332 867.5119) 
(list 1600.4332 867.5222) 
(list 1600.4332 867.5325) 
(list 1600.4332 867.5428) 
(list 1600.4332 867.5531) 
(list 1600.4332 867.5633) 
(list 1600.4332 867.5736) 
(list 1600.4332 867.5839) 
(list 1600.4332 867.5942) 
(list 1600.4332 867.6044) 
(list 1600.4332 867.6147) 
(list 1600.4332 867.625) 
(list 1600.4332 867.6353) 
(list 1600.4332 867.6456) 
(list 1600.4332 867.6558) 
(list 1600.4332 867.6661) 
(list 1600.4332 867.6764) 
(list 1600.4332 867.6867) 
(list 1600.4332 867.6969) 
(list 1600.4332 867.7072) 
(list 1600.4332 867.7175) 
(list 1600.4332 867.7278) 
(list 1600.4332 867.7381) 
(list 1600.4332 867.7483) 
(list 1600.4332 867.7586) 
(list 1600.4332 867.7689) 
(list 1600.4332 867.7792) 
(list 1600.4332 867.7894) 
(list 1600.4332 867.7997) 
(list 1600.4332 867.81) 
(list 1601.092 867.81)))
(apply 'command (append '("pline") coords '("c")))
(setq tap5 (ssadd (entlast) tap5))
(command "_mirror" (entlast) "" "1600,900" "1600,901" "No")
(setq tap5 (ssadd (entlast) tap5))
(setq coords (list 
(list 1600 867.81) 
(list 1600.125 867.81) 
(list 1600.125 867.8203) 
(list 1600.125 867.8306) 
(list 1600.125 867.8408) 
(list 1600.125 867.8511) 
(list 1600.125 867.8614) 
(list 1600.125 867.8717) 
(list 1600.125 867.8819) 
(list 1600.125 867.8922) 
(list 1600.125 867.9025) 
(list 1600.125 867.9128) 
(list 1600.125 867.9231) 
(list 1600.125 867.9333) 
(list 1600.125 867.9436) 
(list 1600.125 867.9539) 
(list 1600.125 867.9642) 
(list 1600.125 867.9744) 
(list 1600.125 867.9847) 
(list 1600.125 867.995) 
(list 1600.125 868.0053) 
(list 1600.125 868.0156) 
(list 1600.125 868.0258) 
(list 1600.125 868.0361) 
(list 1600.125 868.0464) 
(list 1600.125 868.0567) 
(list 1600.125 868.0669) 
(list 1600.125 868.0772) 
(list 1600.125 868.0875) 
(list 1600.125 868.0978) 
(list 1600.125 868.1081) 
(list 1600.125 868.1183) 
(list 1600.125 868.1286) 
(list 1600.125 868.1389) 
(list 1600.125 868.1492) 
(list 1600.125 868.1594) 
(list 1600.125 868.1697) 
(list 1600.125 868.18) 
(list 1600 868.18)))
(apply 'command (append '("pline") coords '("c")))
(setq tap5 (ssadd (entlast) tap5))
(command "_mirror" (entlast) "" "1600,900" "1600,901" "No")
(setq tap5 (ssadd (entlast) tap5))
(setq coords (list 
(list 1600.4426 867.81) 
(list 1600.4332 867.81) 
(list 1600.4331 867.8203) 
(list 1600.4322 867.8306) 
(list 1600.4305 867.8408) 
(list 1600.4281 867.8511) 
(list 1600.425 867.8614) 
(list 1600.4214 867.8717) 
(list 1600.4172 867.8819) 
(list 1600.4127 867.8922) 
(list 1600.408 867.9025) 
(list 1600.4032 867.9128) 
(list 1600.3985 867.9231) 
(list 1600.394 867.9333) 
(list 1600.3898 867.9436) 
(list 1600.3862 867.9539) 
(list 1600.3831 867.9642) 
(list 1600.3808 867.9744) 
(list 1600.3793 867.9847) 
(list 1600.3786 867.995) 
(list 1600.3789 868.0053) 
(list 1600.38 868.0156) 
(list 1600.3821 868.0258) 
(list 1600.3849 868.0361) 
(list 1600.3886 868.0464) 
(list 1600.3929 868.0567) 
(list 1600.3978 868.0669) 
(list 1600.403 868.0772) 
(list 1600.4085 868.0875) 
(list 1600.4141 868.0978) 
(list 1600.4196 868.1081) 
(list 1600.4248 868.1183) 
(list 1600.4296 868.1286) 
(list 1600.4339 868.1389) 
(list 1600.4374 868.1492) 
(list 1600.4401 868.1594) 
(list 1600.4418 868.1697) 
(list 1600.4426 868.18) 
(list 1600.4426 868.18)))
(apply 'command (append '("pline") coords '("c")))
(setq tap5 (ssadd (entlast) tap5))
(command "_mirror" (entlast) "" "1600,900" "1600,901" "No")
(setq tap5 (ssadd (entlast) tap5))
(setq coords (list 
(list 1601.092 867.81) 
(list 1600.4426 867.81) 
(list 1600.4426 867.8203) 
(list 1600.4426 867.8306) 
(list 1600.4426 867.8408) 
(list 1600.4426 867.8511) 
(list 1600.4426 867.8614) 
(list 1600.4426 867.8717) 
(list 1600.4426 867.8819) 
(list 1600.4426 867.8922) 
(list 1600.4426 867.9025) 
(list 1600.4426 867.9128) 
(list 1600.4426 867.9231) 
(list 1600.4426 867.9333) 
(list 1600.4426 867.9436) 
(list 1600.4426 867.9539) 
(list 1600.4426 867.9642) 
(list 1600.4426 867.9744) 
(list 1600.4426 867.9847) 
(list 1600.4426 867.995) 
(list 1600.4426 868.0053) 
(list 1600.4426 868.0156) 
(list 1600.4426 868.0258) 
(list 1600.4426 868.0361) 
(list 1600.4426 868.0464) 
(list 1600.4426 868.0567) 
(list 1600.4426 868.0669) 
(list 1600.4426 868.0772) 
(list 1600.4426 868.0875) 
(list 1600.4426 868.0978) 
(list 1600.4426 868.1081) 
(list 1600.4426 868.1183) 
(list 1600.4426 868.1286) 
(list 1600.4426 868.1389) 
(list 1600.4426 868.1492) 
(list 1600.4426 868.1594) 
(list 1600.4426 868.1697) 
(list 1600.4426 868.18) 
(list 1601.092 868.18)))
(apply 'command (append '("pline") coords '("c")))
(setq tap5 (ssadd (entlast) tap5))
(command "_mirror" (entlast) "" "1600,900" "1600,901" "No")
(setq tap5 (ssadd (entlast) tap5))
(setq coords (list 
(list 1600 868.18) 
(list 1600.125 868.18) 
(list 1600.125 868.1903) 
(list 1600.125 868.2006) 
(list 1600.125 868.2108) 
(list 1600.125 868.2211) 
(list 1600.125 868.2314) 
(list 1600.125 868.2417) 
(list 1600.125 868.2519) 
(list 1600.125 868.2622) 
(list 1600.125 868.2725) 
(list 1600.125 868.2828) 
(list 1600.125 868.2931) 
(list 1600.125 868.3033) 
(list 1600.125 868.3136) 
(list 1600.125 868.3239) 
(list 1600.125 868.3342) 
(list 1600.125 868.3444) 
(list 1600.125 868.3547) 
(list 1600.125 868.365) 
(list 1600.125 868.3753) 
(list 1600.125 868.3856) 
(list 1600.125 868.3958) 
(list 1600.125 868.4061) 
(list 1600.125 868.4164) 
(list 1600.125 868.4267) 
(list 1600.125 868.4369) 
(list 1600.125 868.4472) 
(list 1600.125 868.4575) 
(list 1600.125 868.4678) 
(list 1600.125 868.4781) 
(list 1600.125 868.4883) 
(list 1600.125 868.4986) 
(list 1600.125 868.5089) 
(list 1600.125 868.5192) 
(list 1600.125 868.5294) 
(list 1600.125 868.5397) 
(list 1600.125 868.55) 
(list 1600 868.55)))
(apply 'command (append '("pline") coords '("c")))
(setq tap5 (ssadd (entlast) tap5))
(command "_mirror" (entlast) "" "1600,900" "1600,901" "No")
(setq tap5 (ssadd (entlast) tap5))
(setq coords (list 
(list 1600.452 868.18) 
(list 1600.4426 868.18) 
(list 1600.4423 868.1903) 
(list 1600.4411 868.2006) 
(list 1600.4388 868.2108) 
(list 1600.4355 868.2211) 
(list 1600.4314 868.2314) 
(list 1600.4265 868.2417) 
(list 1600.4211 868.2519) 
(list 1600.4151 868.2622) 
(list 1600.409 868.2725) 
(list 1600.4027 868.2828) 
(list 1600.3966 868.2931) 
(list 1600.3907 868.3033) 
(list 1600.3853 868.3136) 
(list 1600.3806 868.3239) 
(list 1600.3767 868.3342) 
(list 1600.3738 868.3444) 
(list 1600.3719 868.3547) 
(list 1600.3711 868.365) 
(list 1600.3715 868.3753) 
(list 1600.373 868.3856) 
(list 1600.3757 868.3958) 
(list 1600.3794 868.4061) 
(list 1600.3841 868.4164) 
(list 1600.3896 868.4267) 
(list 1600.3958 868.4369) 
(list 1600.4025 868.4472) 
(list 1600.4094 868.4575) 
(list 1600.4165 868.4678) 
(list 1600.4234 868.4781) 
(list 1600.43 868.4883) 
(list 1600.436 868.4986) 
(list 1600.4413 868.5089) 
(list 1600.4456 868.5192) 
(list 1600.449 868.5294) 
(list 1600.4511 868.5397) 
(list 1600.452 868.55) 
(list 1600.452 868.55)))
(apply 'command (append '("pline") coords '("c")))
(setq tap5 (ssadd (entlast) tap5))
(command "_mirror" (entlast) "" "1600,900" "1600,901" "No")
(setq tap5 (ssadd (entlast) tap5))
(setq coords (list 
(list 1601.092 868.18) 
(list 1600.452 868.18) 
(list 1600.452 868.1903) 
(list 1600.452 868.2006) 
(list 1600.452 868.2108) 
(list 1600.452 868.2211) 
(list 1600.452 868.2314) 
(list 1600.452 868.2417) 
(list 1600.452 868.2519) 
(list 1600.452 868.2622) 
(list 1600.452 868.2725) 
(list 1600.452 868.2828) 
(list 1600.452 868.2931) 
(list 1600.452 868.3033) 
(list 1600.452 868.3136) 
(list 1600.452 868.3239) 
(list 1600.452 868.3342) 
(list 1600.452 868.3444) 
(list 1600.452 868.3547) 
(list 1600.452 868.365) 
(list 1600.452 868.3753) 
(list 1600.452 868.3856) 
(list 1600.452 868.3958) 
(list 1600.452 868.4061) 
(list 1600.452 868.4164) 
(list 1600.452 868.4267) 
(list 1600.452 868.4369) 
(list 1600.452 868.4472) 
(list 1600.452 868.4575) 
(list 1600.452 868.4678) 
(list 1600.452 868.4781) 
(list 1600.452 868.4883) 
(list 1600.452 868.4986) 
(list 1600.452 868.5089) 
(list 1600.452 868.5192) 
(list 1600.452 868.5294) 
(list 1600.452 868.5397) 
(list 1600.452 868.55) 
(list 1601.092 868.55)))
(apply 'command (append '("pline") coords '("c")))
(setq tap5 (ssadd (entlast) tap5))
(command "_mirror" (entlast) "" "1600,900" "1600,901" "No")
(setq tap5 (ssadd (entlast) tap5))
(setq coords (list 
(list 1600 868.55) 
(list 1600.125 868.55) 
(list 1600.125 868.5603) 
(list 1600.125 868.5706) 
(list 1600.125 868.5808) 
(list 1600.125 868.5911) 
(list 1600.125 868.6014) 
(list 1600.125 868.6117) 
(list 1600.125 868.6219) 
(list 1600.125 868.6322) 
(list 1600.125 868.6425) 
(list 1600.125 868.6528) 
(list 1600.125 868.6631) 
(list 1600.125 868.6733) 
(list 1600.125 868.6836) 
(list 1600.125 868.6939) 
(list 1600.125 868.7042) 
(list 1600.125 868.7144) 
(list 1600.125 868.7247) 
(list 1600.125 868.735) 
(list 1600.125 868.7453) 
(list 1600.125 868.7556) 
(list 1600.125 868.7658) 
(list 1600.125 868.7761) 
(list 1600.125 868.7864) 
(list 1600.125 868.7967) 
(list 1600.125 868.8069) 
(list 1600.125 868.8172) 
(list 1600.125 868.8275) 
(list 1600.125 868.8378) 
(list 1600.125 868.8481) 
(list 1600.125 868.8583) 
(list 1600.125 868.8686) 
(list 1600.125 868.8789) 
(list 1600.125 868.8892) 
(list 1600.125 868.8994) 
(list 1600.125 868.9097) 
(list 1600.125 868.92) 
(list 1600 868.92)))
(apply 'command (append '("pline") coords '("c")))
(setq tap5 (ssadd (entlast) tap5))
(command "_mirror" (entlast) "" "1600,900" "1600,901" "No")
(setq tap5 (ssadd (entlast) tap5))
(setq coords (list 
(list 1600.4614 868.55) 
(list 1600.452 868.55) 
(list 1600.4516 868.5603) 
(list 1600.4499 868.5706) 
(list 1600.447 868.5808) 
(list 1600.4429 868.5911) 
(list 1600.4378 868.6014) 
(list 1600.4317 868.6117) 
(list 1600.4249 868.6219) 
(list 1600.4176 868.6322) 
(list 1600.4099 868.6425) 
(list 1600.4022 868.6528) 
(list 1600.3946 868.6631) 
(list 1600.3874 868.6733) 
(list 1600.3808 868.6836) 
(list 1600.3751 868.6939) 
(list 1600.3703 868.7042) 
(list 1600.3668 868.7144) 
(list 1600.3645 868.7247) 
(list 1600.3636 868.735) 
(list 1600.3641 868.7453) 
(list 1600.366 868.7556) 
(list 1600.3693 868.7658) 
(list 1600.3738 868.7761) 
(list 1600.3796 868.7864) 
(list 1600.3863 868.7967) 
(list 1600.3938 868.8069) 
(list 1600.4019 868.8172) 
(list 1600.4104 868.8275) 
(list 1600.4189 868.8378) 
(list 1600.4272 868.8481) 
(list 1600.4351 868.8583) 
(list 1600.4424 868.8686) 
(list 1600.4487 868.8789) 
(list 1600.4539 868.8892) 
(list 1600.4578 868.8994) 
(list 1600.4604 868.9097) 
(list 1600.4614 868.92) 
(list 1600.4614 868.92)))
(apply 'command (append '("pline") coords '("c")))
(setq tap5 (ssadd (entlast) tap5))
(command "_mirror" (entlast) "" "1600,900" "1600,901" "No")
(setq tap5 (ssadd (entlast) tap5))
(setq coords (list 
(list 1601.092 868.55) 
(list 1600.4614 868.55) 
(list 1600.4614 868.5603) 
(list 1600.4614 868.5706) 
(list 1600.4614 868.5808) 
(list 1600.4614 868.5911) 
(list 1600.4614 868.6014) 
(list 1600.4614 868.6117) 
(list 1600.4614 868.6219) 
(list 1600.4614 868.6322) 
(list 1600.4614 868.6425) 
(list 1600.4614 868.6528) 
(list 1600.4614 868.6631) 
(list 1600.4614 868.6733) 
(list 1600.4614 868.6836) 
(list 1600.4614 868.6939) 
(list 1600.4614 868.7042) 
(list 1600.4614 868.7144) 
(list 1600.4614 868.7247) 
(list 1600.4614 868.735) 
(list 1600.4614 868.7453) 
(list 1600.4614 868.7556) 
(list 1600.4614 868.7658) 
(list 1600.4614 868.7761) 
(list 1600.4614 868.7864) 
(list 1600.4614 868.7967) 
(list 1600.4614 868.8069) 
(list 1600.4614 868.8172) 
(list 1600.4614 868.8275) 
(list 1600.4614 868.8378) 
(list 1600.4614 868.8481) 
(list 1600.4614 868.8583) 
(list 1600.4614 868.8686) 
(list 1600.4614 868.8789) 
(list 1600.4614 868.8892) 
(list 1600.4614 868.8994) 
(list 1600.4614 868.9097) 
(list 1600.4614 868.92) 
(list 1601.092 868.92)))
(apply 'command (append '("pline") coords '("c")))
(setq tap5 (ssadd (entlast) tap5))
(command "_mirror" (entlast) "" "1600,900" "1600,901" "No")
(setq tap5 (ssadd (entlast) tap5))
(setq coords (list 
(list 1600 868.92) 
(list 1600.125 868.92) 
(list 1600.125 868.9303) 
(list 1600.125 868.9406) 
(list 1600.125 868.9508) 
(list 1600.125 868.9611) 
(list 1600.125 868.9714) 
(list 1600.125 868.9817) 
(list 1600.125 868.9919) 
(list 1600.125 869.0022) 
(list 1600.125 869.0125) 
(list 1600.125 869.0228) 
(list 1600.125 869.0331) 
(list 1600.125 869.0433) 
(list 1600.125 869.0536) 
(list 1600.125 869.0639) 
(list 1600.125 869.0742) 
(list 1600.125 869.0844) 
(list 1600.125 869.0947) 
(list 1600.125 869.105) 
(list 1600.125 869.1153) 
(list 1600.125 869.1256) 
(list 1600.125 869.1358) 
(list 1600.125 869.1461) 
(list 1600.125 869.1564) 
(list 1600.125 869.1667) 
(list 1600.125 869.1769) 
(list 1600.125 869.1872) 
(list 1600.125 869.1975) 
(list 1600.125 869.2078) 
(list 1600.125 869.2181) 
(list 1600.125 869.2283) 
(list 1600.125 869.2386) 
(list 1600.125 869.2489) 
(list 1600.125 869.2592) 
(list 1600.125 869.2694) 
(list 1600.125 869.2797) 
(list 1600.125 869.29) 
(list 1600 869.29)))
(apply 'command (append '("pline") coords '("c")))
(setq tap5 (ssadd (entlast) tap5))
(command "_mirror" (entlast) "" "1600,900" "1600,901" "No")
(setq tap5 (ssadd (entlast) tap5))
(setq coords (list 
(list 1600.4708 868.92) 
(list 1600.4614 868.92) 
(list 1600.4609 868.9303) 
(list 1600.4588 868.9406) 
(list 1600.4553 868.9508) 
(list 1600.4503 868.9611) 
(list 1600.4441 868.9714) 
(list 1600.4369 868.9817) 
(list 1600.4287 868.9919) 
(list 1600.42 869.0022) 
(list 1600.4108 869.0125) 
(list 1600.4016 869.0228) 
(list 1600.3926 869.0331) 
(list 1600.3841 869.0433) 
(list 1600.3763 869.0536) 
(list 1600.3695 869.0639) 
(list 1600.3639 869.0742) 
(list 1600.3597 869.0844) 
(list 1600.3571 869.0947) 
(list 1600.356 869.105) 
(list 1600.3567 869.1153) 
(list 1600.359 869.1256) 
(list 1600.3629 869.1358) 
(list 1600.3683 869.1461) 
(list 1600.3751 869.1564) 
(list 1600.383 869.1667) 
(list 1600.3919 869.1769) 
(list 1600.4014 869.1872) 
(list 1600.4113 869.1975) 
(list 1600.4213 869.2078) 
(list 1600.4311 869.2181) 
(list 1600.4403 869.2283) 
(list 1600.4487 869.2386) 
(list 1600.4561 869.2489) 
(list 1600.4622 869.2592) 
(list 1600.4667 869.2694) 
(list 1600.4696 869.2797) 
(list 1600.4708 869.29) 
(list 1600.4708 869.29)))
(apply 'command (append '("pline") coords '("c")))
(setq tap5 (ssadd (entlast) tap5))
(command "_mirror" (entlast) "" "1600,900" "1600,901" "No")
(setq tap5 (ssadd (entlast) tap5))
(setq coords (list 
(list 1601.092 868.92) 
(list 1600.4708 868.92) 
(list 1600.4708 868.9303) 
(list 1600.4708 868.9406) 
(list 1600.4708 868.9508) 
(list 1600.4708 868.9611) 
(list 1600.4708 868.9714) 
(list 1600.4708 868.9817) 
(list 1600.4708 868.9919) 
(list 1600.4708 869.0022) 
(list 1600.4708 869.0125) 
(list 1600.4708 869.0228) 
(list 1600.4708 869.0331) 
(list 1600.4708 869.0433) 
(list 1600.4708 869.0536) 
(list 1600.4708 869.0639) 
(list 1600.4708 869.0742) 
(list 1600.4708 869.0844) 
(list 1600.4708 869.0947) 
(list 1600.4708 869.105) 
(list 1600.4708 869.1153) 
(list 1600.4708 869.1256) 
(list 1600.4708 869.1358) 
(list 1600.4708 869.1461) 
(list 1600.4708 869.1564) 
(list 1600.4708 869.1667) 
(list 1600.4708 869.1769) 
(list 1600.4708 869.1872) 
(list 1600.4708 869.1975) 
(list 1600.4708 869.2078) 
(list 1600.4708 869.2181) 
(list 1600.4708 869.2283) 
(list 1600.4708 869.2386) 
(list 1600.4708 869.2489) 
(list 1600.4708 869.2592) 
(list 1600.4708 869.2694) 
(list 1600.4708 869.2797) 
(list 1600.4708 869.29) 
(list 1601.092 869.29)))
(apply 'command (append '("pline") coords '("c")))
(setq tap5 (ssadd (entlast) tap5))
(command "_mirror" (entlast) "" "1600,900" "1600,901" "No")
(setq tap5 (ssadd (entlast) tap5))
(setq coords (list 
(list 1600 869.29) 
(list 1600.125 869.29) 
(list 1600.125 869.3003) 
(list 1600.125 869.3106) 
(list 1600.125 869.3208) 
(list 1600.125 869.3311) 
(list 1600.125 869.3414) 
(list 1600.125 869.3517) 
(list 1600.125 869.3619) 
(list 1600.125 869.3722) 
(list 1600.125 869.3825) 
(list 1600.125 869.3928) 
(list 1600.125 869.4031) 
(list 1600.125 869.4133) 
(list 1600.125 869.4236) 
(list 1600.125 869.4339) 
(list 1600.125 869.4442) 
(list 1600.125 869.4544) 
(list 1600.125 869.4647) 
(list 1600.125 869.475) 
(list 1600.125 869.4853) 
(list 1600.125 869.4956) 
(list 1600.125 869.5058) 
(list 1600.125 869.5161) 
(list 1600.125 869.5264) 
(list 1600.125 869.5367) 
(list 1600.125 869.5469) 
(list 1600.125 869.5572) 
(list 1600.125 869.5675) 
(list 1600.125 869.5778) 
(list 1600.125 869.5881) 
(list 1600.125 869.5983) 
(list 1600.125 869.6086) 
(list 1600.125 869.6189) 
(list 1600.125 869.6292) 
(list 1600.125 869.6394) 
(list 1600.125 869.6497) 
(list 1600.125 869.66) 
(list 1600 869.66)))
(apply 'command (append '("pline") coords '("c")))
(setq tap5 (ssadd (entlast) tap5))
(command "_mirror" (entlast) "" "1600,900" "1600,901" "No")
(setq tap5 (ssadd (entlast) tap5))
(setq coords (list 
(list 1600.4802 869.29) 
(list 1600.4708 869.29) 
(list 1600.4702 869.3003) 
(list 1600.4677 869.3106) 
(list 1600.4635 869.3208) 
(list 1600.4578 869.3311) 
(list 1600.4505 869.3414) 
(list 1600.442 869.3517) 
(list 1600.4325 869.3619) 
(list 1600.4224 869.3722) 
(list 1600.4118 869.3825) 
(list 1600.4011 869.3928) 
(list 1600.3907 869.4031) 
(list 1600.3808 869.4133) 
(list 1600.3718 869.4236) 
(list 1600.364 869.4339) 
(list 1600.3575 869.4442) 
(list 1600.3527 869.4544) 
(list 1600.3497 869.4647) 
(list 1600.3485 869.475) 
(list 1600.3493 869.4853) 
(list 1600.3519 869.4956) 
(list 1600.3565 869.5058) 
(list 1600.3627 869.5161) 
(list 1600.3706 869.5264) 
(list 1600.3797 869.5367) 
(list 1600.3899 869.5469) 
(list 1600.4009 869.5572) 
(list 1600.4122 869.5675) 
(list 1600.4237 869.5778) 
(list 1600.4349 869.5881) 
(list 1600.4455 869.5983) 
(list 1600.4551 869.6086) 
(list 1600.4635 869.6189) 
(list 1600.4704 869.6292) 
(list 1600.4756 869.6394) 
(list 1600.4789 869.6497) 
(list 1600.4802 869.66) 
(list 1600.4802 869.66)))
(apply 'command (append '("pline") coords '("c")))
(setq tap5 (ssadd (entlast) tap5))
(command "_mirror" (entlast) "" "1600,900" "1600,901" "No")
(setq tap5 (ssadd (entlast) tap5))
(setq coords (list 
(list 1601.092 869.29) 
(list 1600.4802 869.29) 
(list 1600.4802 869.3003) 
(list 1600.4802 869.3106) 
(list 1600.4802 869.3208) 
(list 1600.4802 869.3311) 
(list 1600.4802 869.3414) 
(list 1600.4802 869.3517) 
(list 1600.4802 869.3619) 
(list 1600.4802 869.3722) 
(list 1600.4802 869.3825) 
(list 1600.4802 869.3928) 
(list 1600.4802 869.4031) 
(list 1600.4802 869.4133) 
(list 1600.4802 869.4236) 
(list 1600.4802 869.4339) 
(list 1600.4802 869.4442) 
(list 1600.4802 869.4544) 
(list 1600.4802 869.4647) 
(list 1600.4802 869.475) 
(list 1600.4802 869.4853) 
(list 1600.4802 869.4956) 
(list 1600.4802 869.5058) 
(list 1600.4802 869.5161) 
(list 1600.4802 869.5264) 
(list 1600.4802 869.5367) 
(list 1600.4802 869.5469) 
(list 1600.4802 869.5572) 
(list 1600.4802 869.5675) 
(list 1600.4802 869.5778) 
(list 1600.4802 869.5881) 
(list 1600.4802 869.5983) 
(list 1600.4802 869.6086) 
(list 1600.4802 869.6189) 
(list 1600.4802 869.6292) 
(list 1600.4802 869.6394) 
(list 1600.4802 869.6497) 
(list 1600.4802 869.66) 
(list 1601.092 869.66)))
(apply 'command (append '("pline") coords '("c")))
(setq tap5 (ssadd (entlast) tap5))
(command "_mirror" (entlast) "" "1600,900" "1600,901" "No")
(setq tap5 (ssadd (entlast) tap5))
(setq coords (list 
(list 1600 869.66) 
(list 1600.125 869.66) 
(list 1600.125 869.6703) 
(list 1600.125 869.6806) 
(list 1600.125 869.6908) 
(list 1600.125 869.7011) 
(list 1600.125 869.7114) 
(list 1600.125 869.7217) 
(list 1600.125 869.7319) 
(list 1600.125 869.7422) 
(list 1600.125 869.7525) 
(list 1600.125 869.7628) 
(list 1600.125 869.7731) 
(list 1600.125 869.7833) 
(list 1600.125 869.7936) 
(list 1600.125 869.8039) 
(list 1600.125 869.8142) 
(list 1600.125 869.8244) 
(list 1600.125 869.8347) 
(list 1600.125 869.845) 
(list 1600.125 869.8553) 
(list 1600.125 869.8656) 
(list 1600.125 869.8758) 
(list 1600.125 869.8861) 
(list 1600.125 869.8964) 
(list 1600.125 869.9067) 
(list 1600.125 869.9169) 
(list 1600.125 869.9272) 
(list 1600.125 869.9375) 
(list 1600.125 869.9478) 
(list 1600.125 869.9581) 
(list 1600.125 869.9683) 
(list 1600.125 869.9786) 
(list 1600.125 869.9889) 
(list 1600.125 869.9992) 
(list 1600.125 870.0094) 
(list 1600.125 870.0197) 
(list 1600.125 870.03) 
(list 1600 870.03)))
(apply 'command (append '("pline") coords '("c")))
(setq tap5 (ssadd (entlast) tap5))
(command "_mirror" (entlast) "" "1600,900" "1600,901" "No")
(setq tap5 (ssadd (entlast) tap5))
(setq coords (list 
(list 1600.4896 869.66) 
(list 1600.4802 869.66) 
(list 1600.4794 869.6703) 
(list 1600.4766 869.6806) 
(list 1600.4718 869.6908) 
(list 1600.4652 869.7011) 
(list 1600.4569 869.7114) 
(list 1600.4472 869.7217) 
(list 1600.4364 869.7319) 
(list 1600.4248 869.7422) 
(list 1600.4127 869.7525) 
(list 1600.4006 869.7628) 
(list 1600.3887 869.7731) 
(list 1600.3775 869.7833) 
(list 1600.3673 869.7936) 
(list 1600.3584 869.8039) 
(list 1600.3511 869.8142) 
(list 1600.3457 869.8244) 
(list 1600.3423 869.8347) 
(list 1600.341 869.845) 
(list 1600.3419 869.8553) 
(list 1600.3449 869.8656) 
(list 1600.3501 869.8758) 
(list 1600.3572 869.8861) 
(list 1600.366 869.8964) 
(list 1600.3764 869.9067) 
(list 1600.3879 869.9169) 
(list 1600.4003 869.9272) 
(list 1600.4132 869.9375) 
(list 1600.4261 869.9478) 
(list 1600.4387 869.9581) 
(list 1600.4506 869.9683) 
(list 1600.4615 869.9786) 
(list 1600.4709 869.9889) 
(list 1600.4787 869.9992) 
(list 1600.4845 870.0094) 
(list 1600.4882 870.0197) 
(list 1600.4896 870.03) 
(list 1600.4896 870.03)))
(apply 'command (append '("pline") coords '("c")))
(setq tap5 (ssadd (entlast) tap5))
(command "_mirror" (entlast) "" "1600,900" "1600,901" "No")
(setq tap5 (ssadd (entlast) tap5))
(setq coords (list 
(list 1601.092 869.66) 
(list 1600.4896 869.66) 
(list 1600.4896 869.6703) 
(list 1600.4896 869.6806) 
(list 1600.4896 869.6908) 
(list 1600.4896 869.7011) 
(list 1600.4896 869.7114) 
(list 1600.4896 869.7217) 
(list 1600.4896 869.7319) 
(list 1600.4896 869.7422) 
(list 1600.4896 869.7525) 
(list 1600.4896 869.7628) 
(list 1600.4896 869.7731) 
(list 1600.4896 869.7833) 
(list 1600.4896 869.7936) 
(list 1600.4896 869.8039) 
(list 1600.4896 869.8142) 
(list 1600.4896 869.8244) 
(list 1600.4896 869.8347) 
(list 1600.4896 869.845) 
(list 1600.4896 869.8553) 
(list 1600.4896 869.8656) 
(list 1600.4896 869.8758) 
(list 1600.4896 869.8861) 
(list 1600.4896 869.8964) 
(list 1600.4896 869.9067) 
(list 1600.4896 869.9169) 
(list 1600.4896 869.9272) 
(list 1600.4896 869.9375) 
(list 1600.4896 869.9478) 
(list 1600.4896 869.9581) 
(list 1600.4896 869.9683) 
(list 1600.4896 869.9786) 
(list 1600.4896 869.9889) 
(list 1600.4896 869.9992) 
(list 1600.4896 870.0094) 
(list 1600.4896 870.0197) 
(list 1600.4896 870.03) 
(list 1601.092 870.03)))
(apply 'command (append '("pline") coords '("c")))
(setq tap5 (ssadd (entlast) tap5))
(command "_mirror" (entlast) "" "1600,900" "1600,901" "No")
(setq tap5 (ssadd (entlast) tap5))
(setq coords (list 
(list 1600 870.03) 
(list 1600.125 870.03) 
(list 1600.125 870.0403) 
(list 1600.125 870.0506) 
(list 1600.125 870.0608) 
(list 1600.125 870.0711) 
(list 1600.125 870.0814) 
(list 1600.125 870.0917) 
(list 1600.125 870.1019) 
(list 1600.125 870.1122) 
(list 1600.125 870.1225) 
(list 1600.125 870.1328) 
(list 1600.125 870.1431) 
(list 1600.125 870.1533) 
(list 1600.125 870.1636) 
(list 1600.125 870.1739) 
(list 1600.125 870.1842) 
(list 1600.125 870.1944) 
(list 1600.125 870.2047) 
(list 1600.125 870.215) 
(list 1600.125 870.2253) 
(list 1600.125 870.2356) 
(list 1600.125 870.2458) 
(list 1600.125 870.2561) 
(list 1600.125 870.2664) 
(list 1600.125 870.2767) 
(list 1600.125 870.2869) 
(list 1600.125 870.2972) 
(list 1600.125 870.3075) 
(list 1600.125 870.3178) 
(list 1600.125 870.3281) 
(list 1600.125 870.3383) 
(list 1600.125 870.3486) 
(list 1600.125 870.3589) 
(list 1600.125 870.3692) 
(list 1600.125 870.3794) 
(list 1600.125 870.3897) 
(list 1600.125 870.4) 
(list 1600 870.4)))
(apply 'command (append '("pline") coords '("c")))
(setq tap5 (ssadd (entlast) tap5))
(command "_mirror" (entlast) "" "1600,900" "1600,901" "No")
(setq tap5 (ssadd (entlast) tap5))
(setq coords (list 
(list 1600.499 870.03) 
(list 1600.4896 870.03) 
(list 1600.4887 870.0403) 
(list 1600.4855 870.0506) 
(list 1600.4801 870.0608) 
(list 1600.4726 870.0711) 
(list 1600.4633 870.0814) 
(list 1600.4524 870.0917) 
(list 1600.4402 870.1019) 
(list 1600.4272 870.1122) 
(list 1600.4136 870.1225) 
(list 1600.4 870.1328) 
(list 1600.3867 870.1431) 
(list 1600.3742 870.1533) 
(list 1600.3628 870.1636) 
(list 1600.3529 870.1739) 
(list 1600.3447 870.1842) 
(list 1600.3387 870.1944) 
(list 1600.3349 870.2047) 
(list 1600.3334 870.215) 
(list 1600.3344 870.2253) 
(list 1600.3379 870.2356) 
(list 1600.3437 870.2458) 
(list 1600.3516 870.2561) 
(list 1600.3615 870.2664) 
(list 1600.3731 870.2767) 
(list 1600.386 870.2869) 
(list 1600.3998 870.2972) 
(list 1600.4141 870.3075) 
(list 1600.4285 870.3178) 
(list 1600.4425 870.3281) 
(list 1600.4558 870.3383) 
(list 1600.4679 870.3486) 
(list 1600.4784 870.3589) 
(list 1600.487 870.3692) 
(list 1600.4934 870.3794) 
(list 1600.4975 870.3897) 
(list 1600.499 870.4) 
(list 1600.499 870.4)))
(apply 'command (append '("pline") coords '("c")))
(setq tap5 (ssadd (entlast) tap5))
(command "_mirror" (entlast) "" "1600,900" "1600,901" "No")
(setq tap5 (ssadd (entlast) tap5))
(setq coords (list 
(list 1601.092 870.03) 
(list 1600.499 870.03) 
(list 1600.499 870.0403) 
(list 1600.499 870.0506) 
(list 1600.499 870.0608) 
(list 1600.499 870.0711) 
(list 1600.499 870.0814) 
(list 1600.499 870.0917) 
(list 1600.499 870.1019) 
(list 1600.499 870.1122) 
(list 1600.499 870.1225) 
(list 1600.499 870.1328) 
(list 1600.499 870.1431) 
(list 1600.499 870.1533) 
(list 1600.499 870.1636) 
(list 1600.499 870.1739) 
(list 1600.499 870.1842) 
(list 1600.499 870.1944) 
(list 1600.499 870.2047) 
(list 1600.499 870.215) 
(list 1600.499 870.2253) 
(list 1600.499 870.2356) 
(list 1600.499 870.2458) 
(list 1600.499 870.2561) 
(list 1600.499 870.2664) 
(list 1600.499 870.2767) 
(list 1600.499 870.2869) 
(list 1600.499 870.2972) 
(list 1600.499 870.3075) 
(list 1600.499 870.3178) 
(list 1600.499 870.3281) 
(list 1600.499 870.3383) 
(list 1600.499 870.3486) 
(list 1600.499 870.3589) 
(list 1600.499 870.3692) 
(list 1600.499 870.3794) 
(list 1600.499 870.3897) 
(list 1600.499 870.4) 
(list 1601.092 870.4)))
(apply 'command (append '("pline") coords '("c")))
(setq tap5 (ssadd (entlast) tap5))
(command "_mirror" (entlast) "" "1600,900" "1600,901" "No")
(setq tap5 (ssadd (entlast) tap5))
(setq coords (list 
(list 1600 870.4) 
(list 1600.125 870.4) 
(list 1600.125 870.4103) 
(list 1600.125 870.4206) 
(list 1600.125 870.4308) 
(list 1600.125 870.4411) 
(list 1600.125 870.4514) 
(list 1600.125 870.4617) 
(list 1600.125 870.4719) 
(list 1600.125 870.4822) 
(list 1600.125 870.4925) 
(list 1600.125 870.5028) 
(list 1600.125 870.5131) 
(list 1600.125 870.5233) 
(list 1600.125 870.5336) 
(list 1600.125 870.5439) 
(list 1600.125 870.5542) 
(list 1600.125 870.5644) 
(list 1600.125 870.5747) 
(list 1600.125 870.585) 
(list 1600.125 870.5953) 
(list 1600.125 870.6056) 
(list 1600.125 870.6158) 
(list 1600.125 870.6261) 
(list 1600.125 870.6364) 
(list 1600.125 870.6467) 
(list 1600.125 870.6569) 
(list 1600.125 870.6672) 
(list 1600.125 870.6775) 
(list 1600.125 870.6878) 
(list 1600.125 870.6981) 
(list 1600.125 870.7083) 
(list 1600.125 870.7186) 
(list 1600.125 870.7289) 
(list 1600.125 870.7392) 
(list 1600.125 870.7494) 
(list 1600.125 870.7597) 
(list 1600.125 870.77) 
(list 1600 870.77)))
(apply 'command (append '("pline") coords '("c")))
(setq tap5 (ssadd (entlast) tap5))
(command "_mirror" (entlast) "" "1600,900" "1600,901" "No")
(setq tap5 (ssadd (entlast) tap5))
(setq coords (list 
(list 1600.5084 870.4) 
(list 1600.499 870.4) 
(list 1600.498 870.4103) 
(list 1600.4944 870.4206) 
(list 1600.4883 870.4308) 
(list 1600.48 870.4411) 
(list 1600.4696 870.4514) 
(list 1600.4575 870.4617) 
(list 1600.444 870.4719) 
(list 1600.4296 870.4822) 
(list 1600.4146 870.4925) 
(list 1600.3995 870.5028) 
(list 1600.3848 870.5131) 
(list 1600.3709 870.5233) 
(list 1600.3583 870.5336) 
(list 1600.3473 870.5439) 
(list 1600.3383 870.5542) 
(list 1600.3317 870.5644) 
(list 1600.3275 870.5747) 
(list 1600.3259 870.585) 
(list 1600.327 870.5953) 
(list 1600.3309 870.6056) 
(list 1600.3373 870.6158) 
(list 1600.3461 870.6261) 
(list 1600.357 870.6364) 
(list 1600.3698 870.6467) 
(list 1600.384 870.6569) 
(list 1600.3992 870.6672) 
(list 1600.415 870.6775) 
(list 1600.4309 870.6878) 
(list 1600.4464 870.6981) 
(list 1600.461 870.7083) 
(list 1600.4742 870.7186) 
(list 1600.4858 870.7289) 
(list 1600.4952 870.7392) 
(list 1600.5023 870.7494) 
(list 1600.5067 870.7597) 
(list 1600.5084 870.77) 
(list 1600.5084 870.77)))
(apply 'command (append '("pline") coords '("c")))
(setq tap5 (ssadd (entlast) tap5))
(command "_mirror" (entlast) "" "1600,900" "1600,901" "No")
(setq tap5 (ssadd (entlast) tap5))
(setq coords (list 
(list 1601.092 870.4) 
(list 1600.5084 870.4) 
(list 1600.5084 870.4103) 
(list 1600.5084 870.4206) 
(list 1600.5084 870.4308) 
(list 1600.5084 870.4411) 
(list 1600.5084 870.4514) 
(list 1600.5084 870.4617) 
(list 1600.5084 870.4719) 
(list 1600.5084 870.4822) 
(list 1600.5084 870.4925) 
(list 1600.5084 870.5028) 
(list 1600.5084 870.5131) 
(list 1600.5084 870.5233) 
(list 1600.5084 870.5336) 
(list 1600.5084 870.5439) 
(list 1600.5084 870.5542) 
(list 1600.5084 870.5644) 
(list 1600.5084 870.5747) 
(list 1600.5084 870.585) 
(list 1600.5084 870.5953) 
(list 1600.5084 870.6056) 
(list 1600.5084 870.6158) 
(list 1600.5084 870.6261) 
(list 1600.5084 870.6364) 
(list 1600.5084 870.6467) 
(list 1600.5084 870.6569) 
(list 1600.5084 870.6672) 
(list 1600.5084 870.6775) 
(list 1600.5084 870.6878) 
(list 1600.5084 870.6981) 
(list 1600.5084 870.7083) 
(list 1600.5084 870.7186) 
(list 1600.5084 870.7289) 
(list 1600.5084 870.7392) 
(list 1600.5084 870.7494) 
(list 1600.5084 870.7597) 
(list 1600.5084 870.77) 
(list 1601.092 870.77)))
(apply 'command (append '("pline") coords '("c")))
(setq tap5 (ssadd (entlast) tap5))
(command "_mirror" (entlast) "" "1600,900" "1600,901" "No")
(setq tap5 (ssadd (entlast) tap5))
(setq coords (list 
(list 1600 870.77) 
(list 1600.125 870.77) 
(list 1600.125 870.7803) 
(list 1600.125 870.7906) 
(list 1600.125 870.8008) 
(list 1600.125 870.8111) 
(list 1600.125 870.8214) 
(list 1600.125 870.8317) 
(list 1600.125 870.8419) 
(list 1600.125 870.8522) 
(list 1600.125 870.8625) 
(list 1600.125 870.8728) 
(list 1600.125 870.8831) 
(list 1600.125 870.8933) 
(list 1600.125 870.9036) 
(list 1600.125 870.9139) 
(list 1600.125 870.9242) 
(list 1600.125 870.9344) 
(list 1600.125 870.9447) 
(list 1600.125 870.955) 
(list 1600.125 870.9653) 
(list 1600.125 870.9756) 
(list 1600.125 870.9858) 
(list 1600.125 870.9961) 
(list 1600.125 871.0064) 
(list 1600.125 871.0167) 
(list 1600.125 871.0269) 
(list 1600.125 871.0372) 
(list 1600.125 871.0475) 
(list 1600.125 871.0578) 
(list 1600.125 871.0681) 
(list 1600.125 871.0783) 
(list 1600.125 871.0886) 
(list 1600.125 871.0989) 
(list 1600.125 871.1092) 
(list 1600.125 871.1194) 
(list 1600.125 871.1297) 
(list 1600.125 871.14) 
(list 1600 871.14)))
(apply 'command (append '("pline") coords '("c")))
(setq tap5 (ssadd (entlast) tap5))
(command "_mirror" (entlast) "" "1600,900" "1600,901" "No")
(setq tap5 (ssadd (entlast) tap5))
(setq coords (list 
(list 1600.5178 870.77) 
(list 1600.5084 870.77) 
(list 1600.5072 870.7803) 
(list 1600.5033 870.7906) 
(list 1600.4966 870.8008) 
(list 1600.4874 870.8111) 
(list 1600.476 870.8214) 
(list 1600.4627 870.8317) 
(list 1600.4479 870.8419) 
(list 1600.432 870.8522) 
(list 1600.4155 870.8625) 
(list 1600.3989 870.8728) 
(list 1600.3828 870.8831) 
(list 1600.3676 870.8933) 
(list 1600.3538 870.9036) 
(list 1600.3418 870.9139) 
(list 1600.3319 870.9242) 
(list 1600.3246 870.9344) 
(list 1600.3201 870.9447) 
(list 1600.3184 870.955) 
(list 1600.3196 870.9653) 
(list 1600.3238 870.9756) 
(list 1600.3309 870.9858) 
(list 1600.3405 870.9961) 
(list 1600.3525 871.0064) 
(list 1600.3665 871.0167) 
(list 1600.382 871.0269) 
(list 1600.3987 871.0372) 
(list 1600.416 871.0475) 
(list 1600.4333 871.0578) 
(list 1600.4502 871.0681) 
(list 1600.4661 871.0783) 
(list 1600.4806 871.0886) 
(list 1600.4932 871.0989) 
(list 1600.5035 871.1092) 
(list 1600.5112 871.1194) 
(list 1600.516 871.1297) 
(list 1600.5178 871.14) 
(list 1600.5178 871.14)))
(apply 'command (append '("pline") coords '("c")))
(setq tap5 (ssadd (entlast) tap5))
(command "_mirror" (entlast) "" "1600,900" "1600,901" "No")
(setq tap5 (ssadd (entlast) tap5))
(setq coords (list 
(list 1601.092 870.77) 
(list 1600.5178 870.77) 
(list 1600.5178 870.7803) 
(list 1600.5178 870.7906) 
(list 1600.5178 870.8008) 
(list 1600.5178 870.8111) 
(list 1600.5178 870.8214) 
(list 1600.5178 870.8317) 
(list 1600.5178 870.8419) 
(list 1600.5178 870.8522) 
(list 1600.5178 870.8625) 
(list 1600.5178 870.8728) 
(list 1600.5178 870.8831) 
(list 1600.5178 870.8933) 
(list 1600.5178 870.9036) 
(list 1600.5178 870.9139) 
(list 1600.5178 870.9242) 
(list 1600.5178 870.9344) 
(list 1600.5178 870.9447) 
(list 1600.5178 870.955) 
(list 1600.5178 870.9653) 
(list 1600.5178 870.9756) 
(list 1600.5178 870.9858) 
(list 1600.5178 870.9961) 
(list 1600.5178 871.0064) 
(list 1600.5178 871.0167) 
(list 1600.5178 871.0269) 
(list 1600.5178 871.0372) 
(list 1600.5178 871.0475) 
(list 1600.5178 871.0578) 
(list 1600.5178 871.0681) 
(list 1600.5178 871.0783) 
(list 1600.5178 871.0886) 
(list 1600.5178 871.0989) 
(list 1600.5178 871.1092) 
(list 1600.5178 871.1194) 
(list 1600.5178 871.1297) 
(list 1600.5178 871.14) 
(list 1601.092 871.14)))
(apply 'command (append '("pline") coords '("c")))
(setq tap5 (ssadd (entlast) tap5))
(command "_mirror" (entlast) "" "1600,900" "1600,901" "No")
(setq tap5 (ssadd (entlast) tap5))
(setq coords (list 
(list 1600 871.14) 
(list 1600.125 871.14) 
(list 1600.125 871.1503) 
(list 1600.125 871.1606) 
(list 1600.125 871.1708) 
(list 1600.125 871.1811) 
(list 1600.125 871.1914) 
(list 1600.125 871.2017) 
(list 1600.125 871.2119) 
(list 1600.125 871.2222) 
(list 1600.125 871.2325) 
(list 1600.125 871.2428) 
(list 1600.125 871.2531) 
(list 1600.125 871.2633) 
(list 1600.125 871.2736) 
(list 1600.125 871.2839) 
(list 1600.125 871.2942) 
(list 1600.125 871.3044) 
(list 1600.125 871.3147) 
(list 1600.125 871.325) 
(list 1600.125 871.3353) 
(list 1600.125 871.3456) 
(list 1600.125 871.3558) 
(list 1600.125 871.3661) 
(list 1600.125 871.3764) 
(list 1600.125 871.3867) 
(list 1600.125 871.3969) 
(list 1600.125 871.4072) 
(list 1600.125 871.4175) 
(list 1600.125 871.4278) 
(list 1600.125 871.4381) 
(list 1600.125 871.4483) 
(list 1600.125 871.4586) 
(list 1600.125 871.4689) 
(list 1600.125 871.4792) 
(list 1600.125 871.4894) 
(list 1600.125 871.4997) 
(list 1600.125 871.51) 
(list 1600 871.51)))
(apply 'command (append '("pline") coords '("c")))
(setq tap5 (ssadd (entlast) tap5))
(command "_mirror" (entlast) "" "1600,900" "1600,901" "No")
(setq tap5 (ssadd (entlast) tap5))
(setq coords (list 
(list 1600.5272 871.14) 
(list 1600.5178 871.14) 
(list 1600.5165 871.1503) 
(list 1600.5122 871.1606) 
(list 1600.5049 871.1708) 
(list 1600.4949 871.1811) 
(list 1600.4824 871.1914) 
(list 1600.4679 871.2017) 
(list 1600.4517 871.2119) 
(list 1600.4344 871.2222) 
(list 1600.4164 871.2325) 
(list 1600.3984 871.2428) 
(list 1600.3809 871.2531) 
(list 1600.3643 871.2633) 
(list 1600.3493 871.2736) 
(list 1600.3362 871.2839) 
(list 1600.3255 871.2942) 
(list 1600.3176 871.3044) 
(list 1600.3126 871.3147) 
(list 1600.3108 871.325) 
(list 1600.3122 871.3353) 
(list 1600.3168 871.3456) 
(list 1600.3245 871.3558) 
(list 1600.335 871.3661) 
(list 1600.348 871.3764) 
(list 1600.3632 871.3867) 
(list 1600.3801 871.3969) 
(list 1600.3982 871.4072) 
(list 1600.4169 871.4175) 
(list 1600.4357 871.4278) 
(list 1600.454 871.4381) 
(list 1600.4713 871.4483) 
(list 1600.487 871.4586) 
(list 1600.5006 871.4689) 
(list 1600.5118 871.4792) 
(list 1600.5201 871.4894) 
(list 1600.5253 871.4997) 
(list 1600.5272 871.51) 
(list 1600.5272 871.51)))
(apply 'command (append '("pline") coords '("c")))
(setq tap5 (ssadd (entlast) tap5))
(command "_mirror" (entlast) "" "1600,900" "1600,901" "No")
(setq tap5 (ssadd (entlast) tap5))
(setq coords (list 
(list 1601.092 871.14) 
(list 1600.5272 871.14) 
(list 1600.5272 871.1503) 
(list 1600.5272 871.1606) 
(list 1600.5272 871.1708) 
(list 1600.5272 871.1811) 
(list 1600.5272 871.1914) 
(list 1600.5272 871.2017) 
(list 1600.5272 871.2119) 
(list 1600.5272 871.2222) 
(list 1600.5272 871.2325) 
(list 1600.5272 871.2428) 
(list 1600.5272 871.2531) 
(list 1600.5272 871.2633) 
(list 1600.5272 871.2736) 
(list 1600.5272 871.2839) 
(list 1600.5272 871.2942) 
(list 1600.5272 871.3044) 
(list 1600.5272 871.3147) 
(list 1600.5272 871.325) 
(list 1600.5272 871.3353) 
(list 1600.5272 871.3456) 
(list 1600.5272 871.3558) 
(list 1600.5272 871.3661) 
(list 1600.5272 871.3764) 
(list 1600.5272 871.3867) 
(list 1600.5272 871.3969) 
(list 1600.5272 871.4072) 
(list 1600.5272 871.4175) 
(list 1600.5272 871.4278) 
(list 1600.5272 871.4381) 
(list 1600.5272 871.4483) 
(list 1600.5272 871.4586) 
(list 1600.5272 871.4689) 
(list 1600.5272 871.4792) 
(list 1600.5272 871.4894) 
(list 1600.5272 871.4997) 
(list 1600.5272 871.51) 
(list 1601.092 871.51)))
(apply 'command (append '("pline") coords '("c")))
(setq tap5 (ssadd (entlast) tap5))
(command "_mirror" (entlast) "" "1600,900" "1600,901" "No")
(setq tap5 (ssadd (entlast) tap5))
(setq coords (list 
(list 1600 871.51) 
(list 1600.125 871.51) 
(list 1600.125 871.5203) 
(list 1600.125 871.5306) 
(list 1600.125 871.5408) 
(list 1600.125 871.5511) 
(list 1600.125 871.5614) 
(list 1600.125 871.5717) 
(list 1600.125 871.5819) 
(list 1600.125 871.5922) 
(list 1600.125 871.6025) 
(list 1600.125 871.6128) 
(list 1600.125 871.6231) 
(list 1600.125 871.6333) 
(list 1600.125 871.6436) 
(list 1600.125 871.6539) 
(list 1600.125 871.6642) 
(list 1600.125 871.6744) 
(list 1600.125 871.6847) 
(list 1600.125 871.695) 
(list 1600.125 871.7053) 
(list 1600.125 871.7156) 
(list 1600.125 871.7258) 
(list 1600.125 871.7361) 
(list 1600.125 871.7464) 
(list 1600.125 871.7567) 
(list 1600.125 871.7669) 
(list 1600.125 871.7772) 
(list 1600.125 871.7875) 
(list 1600.125 871.7978) 
(list 1600.125 871.8081) 
(list 1600.125 871.8183) 
(list 1600.125 871.8286) 
(list 1600.125 871.8389) 
(list 1600.125 871.8492) 
(list 1600.125 871.8594) 
(list 1600.125 871.8697) 
(list 1600.125 871.88) 
(list 1600 871.88)))
(apply 'command (append '("pline") coords '("c")))
(setq tap5 (ssadd (entlast) tap5))
(command "_mirror" (entlast) "" "1600,900" "1600,901" "No")
(setq tap5 (ssadd (entlast) tap5))
(setq coords (list 
(list 1600.5366 871.51) 
(list 1600.5272 871.51) 
(list 1600.5258 871.5203) 
(list 1600.5211 871.5306) 
(list 1600.5131 871.5408) 
(list 1600.5023 871.5511) 
(list 1600.4888 871.5614) 
(list 1600.473 871.5717) 
(list 1600.4555 871.5819) 
(list 1600.4368 871.5922) 
(list 1600.4174 871.6025) 
(list 1600.3979 871.6128) 
(list 1600.3789 871.6231) 
(list 1600.361 871.6333) 
(list 1600.3448 871.6436) 
(list 1600.3307 871.6539) 
(list 1600.3191 871.6642) 
(list 1600.3106 871.6744) 
(list 1600.3052 871.6847) 
(list 1600.3033 871.695) 
(list 1600.3048 871.7053) 
(list 1600.3098 871.7156) 
(list 1600.3181 871.7258) 
(list 1600.3294 871.7361) 
(list 1600.3435 871.7464) 
(list 1600.3599 871.7567) 
(list 1600.3781 871.7669) 
(list 1600.3976 871.7772) 
(list 1600.4178 871.7875) 
(list 1600.4381 871.7978) 
(list 1600.4579 871.8081) 
(list 1600.4765 871.8183) 
(list 1600.4934 871.8286) 
(list 1600.508 871.8389) 
(list 1600.52 871.8492) 
(list 1600.529 871.8594) 
(list 1600.5345 871.8697) 
(list 1600.5366 871.88) 
(list 1600.5366 871.88)))
(apply 'command (append '("pline") coords '("c")))
(setq tap5 (ssadd (entlast) tap5))
(command "_mirror" (entlast) "" "1600,900" "1600,901" "No")
(setq tap5 (ssadd (entlast) tap5))
(setq coords (list 
(list 1601.092 871.51) 
(list 1600.5366 871.51) 
(list 1600.5366 871.5203) 
(list 1600.5366 871.5306) 
(list 1600.5366 871.5408) 
(list 1600.5366 871.5511) 
(list 1600.5366 871.5614) 
(list 1600.5366 871.5717) 
(list 1600.5366 871.5819) 
(list 1600.5366 871.5922) 
(list 1600.5366 871.6025) 
(list 1600.5366 871.6128) 
(list 1600.5366 871.6231) 
(list 1600.5366 871.6333) 
(list 1600.5366 871.6436) 
(list 1600.5366 871.6539) 
(list 1600.5366 871.6642) 
(list 1600.5366 871.6744) 
(list 1600.5366 871.6847) 
(list 1600.5366 871.695) 
(list 1600.5366 871.7053) 
(list 1600.5366 871.7156) 
(list 1600.5366 871.7258) 
(list 1600.5366 871.7361) 
(list 1600.5366 871.7464) 
(list 1600.5366 871.7567) 
(list 1600.5366 871.7669) 
(list 1600.5366 871.7772) 
(list 1600.5366 871.7875) 
(list 1600.5366 871.7978) 
(list 1600.5366 871.8081) 
(list 1600.5366 871.8183) 
(list 1600.5366 871.8286) 
(list 1600.5366 871.8389) 
(list 1600.5366 871.8492) 
(list 1600.5366 871.8594) 
(list 1600.5366 871.8697) 
(list 1600.5366 871.88) 
(list 1601.092 871.88)))
(apply 'command (append '("pline") coords '("c")))
(setq tap5 (ssadd (entlast) tap5))
(command "_mirror" (entlast) "" "1600,900" "1600,901" "No")
(setq tap5 (ssadd (entlast) tap5))
(setq coords (list 
(list 1600 871.88) 
(list 1600.125 871.88) 
(list 1600.125 871.8903) 
(list 1600.125 871.9006) 
(list 1600.125 871.9108) 
(list 1600.125 871.9211) 
(list 1600.125 871.9314) 
(list 1600.125 871.9417) 
(list 1600.125 871.9519) 
(list 1600.125 871.9622) 
(list 1600.125 871.9725) 
(list 1600.125 871.9828) 
(list 1600.125 871.9931) 
(list 1600.125 872.0033) 
(list 1600.125 872.0136) 
(list 1600.125 872.0239) 
(list 1600.125 872.0342) 
(list 1600.125 872.0444) 
(list 1600.125 872.0547) 
(list 1600.125 872.065) 
(list 1600.125 872.0753) 
(list 1600.125 872.0856) 
(list 1600.125 872.0958) 
(list 1600.125 872.1061) 
(list 1600.125 872.1164) 
(list 1600.125 872.1267) 
(list 1600.125 872.1369) 
(list 1600.125 872.1472) 
(list 1600.125 872.1575) 
(list 1600.125 872.1678) 
(list 1600.125 872.1781) 
(list 1600.125 872.1883) 
(list 1600.125 872.1986) 
(list 1600.125 872.2089) 
(list 1600.125 872.2192) 
(list 1600.125 872.2294) 
(list 1600.125 872.2397) 
(list 1600.125 872.25) 
(list 1600 872.25)))
(apply 'command (append '("pline") coords '("c")))
(setq tap5 (ssadd (entlast) tap5))
(command "_mirror" (entlast) "" "1600,900" "1600,901" "No")
(setq tap5 (ssadd (entlast) tap5))
(setq coords (list 
(list 1600.546 871.88) 
(list 1600.5366 871.88) 
(list 1600.5351 871.8903) 
(list 1600.5299 871.9006) 
(list 1600.5214 871.9108) 
(list 1600.5097 871.9211) 
(list 1600.4951 871.9314) 
(list 1600.4782 871.9417) 
(list 1600.4594 871.9519) 
(list 1600.4392 871.9622) 
(list 1600.4183 871.9725) 
(list 1600.3973 871.9828) 
(list 1600.3769 871.9931) 
(list 1600.3577 872.0033) 
(list 1600.3402 872.0136) 
(list 1600.3251 872.0239) 
(list 1600.3127 872.0342) 
(list 1600.3036 872.0444) 
(list 1600.2978 872.0547) 
(list 1600.2958 872.065) 
(list 1600.2974 872.0753) 
(list 1600.3028 872.0856) 
(list 1600.3117 872.0958) 
(list 1600.3239 872.1061) 
(list 1600.339 872.1164) 
(list 1600.3566 872.1267) 
(list 1600.3762 872.1369) 
(list 1600.3971 872.1472) 
(list 1600.4188 872.1575) 
(list 1600.4405 872.1678) 
(list 1600.4617 872.1781) 
(list 1600.4816 872.1883) 
(list 1600.4997 872.1986) 
(list 1600.5155 872.2089) 
(list 1600.5283 872.2192) 
(list 1600.5378 872.2294) 
(list 1600.5438 872.2397) 
(list 1600.546 872.25) 
(list 1600.546 872.25)))
(apply 'command (append '("pline") coords '("c")))
(setq tap5 (ssadd (entlast) tap5))
(command "_mirror" (entlast) "" "1600,900" "1600,901" "No")
(setq tap5 (ssadd (entlast) tap5))
(setq coords (list 
(list 1601.092 871.88) 
(list 1600.546 871.88) 
(list 1600.546 871.8903) 
(list 1600.546 871.9006) 
(list 1600.546 871.9108) 
(list 1600.546 871.9211) 
(list 1600.546 871.9314) 
(list 1600.546 871.9417) 
(list 1600.546 871.9519) 
(list 1600.546 871.9622) 
(list 1600.546 871.9725) 
(list 1600.546 871.9828) 
(list 1600.546 871.9931) 
(list 1600.546 872.0033) 
(list 1600.546 872.0136) 
(list 1600.546 872.0239) 
(list 1600.546 872.0342) 
(list 1600.546 872.0444) 
(list 1600.546 872.0547) 
(list 1600.546 872.065) 
(list 1600.546 872.0753) 
(list 1600.546 872.0856) 
(list 1600.546 872.0958) 
(list 1600.546 872.1061) 
(list 1600.546 872.1164) 
(list 1600.546 872.1267) 
(list 1600.546 872.1369) 
(list 1600.546 872.1472) 
(list 1600.546 872.1575) 
(list 1600.546 872.1678) 
(list 1600.546 872.1781) 
(list 1600.546 872.1883) 
(list 1600.546 872.1986) 
(list 1600.546 872.2089) 
(list 1600.546 872.2192) 
(list 1600.546 872.2294) 
(list 1600.546 872.2397) 
(list 1600.546 872.25) 
(list 1601.092 872.25)))
(apply 'command (append '("pline") coords '("c")))
(setq tap5 (ssadd (entlast) tap5))
(command "_mirror" (entlast) "" "1600,900" "1600,901" "No")
(setq tap5 (ssadd (entlast) tap5))
(command "_block" "blktap5" "1600,900" tap5 "")
(command "_insert" "blktap5" "1600,900" "1" "1" "0")
(command "_insert" "blktap5" "1600,900" "1" "1" "180")
(setq uc5 nil)
(setq uc5 (ssadd))
(setq coords (list 
(list 0 -0.185) 
(list 0.125 -0.185) 
(list 0.125 -0.17472) 
(list 0.125 -0.16444) 
(list 0.125 -0.15417) 
(list 0.125 -0.14389) 
(list 0.125 -0.13361) 
(list 0.125 -0.12333) 
(list 0.125 -0.11306) 
(list 0.125 -0.10278) 
(list 0.125 -0.0925) 
(list 0.125 -0.082222) 
(list 0.125 -0.071944) 
(list 0.125 -0.061667) 
(list 0.125 -0.051389) 
(list 0.125 -0.041111) 
(list 0.125 -0.030833) 
(list 0.125 -0.020556) 
(list 0.125 -0.010278) 
(list 0.125 0) 
(list 0.125 0.010278) 
(list 0.125 0.020556) 
(list 0.125 0.030833) 
(list 0.125 0.041111) 
(list 0.125 0.051389) 
(list 0.125 0.061667) 
(list 0.125 0.071944) 
(list 0.125 0.082222) 
(list 0.125 0.0925) 
(list 0.125 0.10278) 
(list 0.125 0.11306) 
(list 0.125 0.12333) 
(list 0.125 0.13361) 
(list 0.125 0.14389) 
(list 0.125 0.15417) 
(list 0.125 0.16444) 
(list 0.125 0.17472) 
(list 0.125 0.185) 
(list 0 0.185)))
(apply 'command (append '("pline") coords '("c")))
(setq uc5 (ssadd (entlast) uc5))
(setq coords (list 
(list 1.092 -0.185) 
(list 0.546 -0.185) 
(list 0.54407 -0.17472) 
(list 0.53834 -0.16444) 
(list 0.52899 -0.15417) 
(list 0.51629 -0.14389) 
(list 0.50063 -0.13361) 
(list 0.4825 -0.12333) 
(list 0.46244 -0.11306) 
(list 0.44105 -0.10278) 
(list 0.419 -0.0925) 
(list 0.39695 -0.082222) 
(list 0.37556 -0.071944) 
(list 0.3555 -0.061667) 
(list 0.33737 -0.051389) 
(list 0.32171 -0.041111) 
(list 0.30901 -0.030833) 
(list 0.29966 -0.020556) 
(list 0.29393 -0.010278) 
(list 0.292 0) 
(list 0.29393 0.010278) 
(list 0.29966 0.020556) 
(list 0.30901 0.030833) 
(list 0.32171 0.041111) 
(list 0.33737 0.051389) 
(list 0.3555 0.061667) 
(list 0.37556 0.071944) 
(list 0.39695 0.082222) 
(list 0.419 0.0925) 
(list 0.44105 0.10278) 
(list 0.46244 0.11306) 
(list 0.4825 0.12333) 
(list 0.50063 0.13361) 
(list 0.51629 0.14389) 
(list 0.52899 0.15417) 
(list 0.53834 0.16444) 
(list 0.54407 0.17472) 
(list 0.546 0.185) 
(list 1.092 0.185)))
(apply 'command (append '("pline") coords '("c")))
(setq uc5 (ssadd (entlast) uc5))
(command "_block" "blkuc5" "0,0.185" uc5 "")
(command "_insert" "blkuc5" "1600,872.62" "1" "1" "0")
(command "_insert" "blkuc5" "1600,872.25" "1" "1" "180")
(command "_insert" "blkuc5" "1600,872.99" "1" "1" "0")
(command "_insert" "blkuc5" "1600,872.62" "1" "1" "180")
(command "_insert" "blkuc5" "1600,873.36" "1" "1" "0")
(command "_insert" "blkuc5" "1600,872.99" "1" "1" "180")
(command "_insert" "blkuc5" "1600,873.73" "1" "1" "0")
(command "_insert" "blkuc5" "1600,873.36" "1" "1" "180")
(command "_insert" "blkuc5" "1600,874.1" "1" "1" "0")
(command "_insert" "blkuc5" "1600,873.73" "1" "1" "180")
(command "_insert" "blkuc5" "1600,874.47" "1" "1" "0")
(command "_insert" "blkuc5" "1600,874.1" "1" "1" "180")
(command "_insert" "blkuc5" "1600,874.84" "1" "1" "0")
(command "_insert" "blkuc5" "1600,874.47" "1" "1" "180")
(command "_insert" "blkuc5" "1600,875.21" "1" "1" "0")
(command "_insert" "blkuc5" "1600,874.84" "1" "1" "180")
(command "_insert" "blkuc5" "1600,875.58" "1" "1" "0")
(command "_insert" "blkuc5" "1600,875.21" "1" "1" "180")
(command "_insert" "blkuc5" "1600,875.95" "1" "1" "0")
(command "_insert" "blkuc5" "1600,875.58" "1" "1" "180")
(command "_insert" "blkuc5" "1600,876.32" "1" "1" "0")
(command "_insert" "blkuc5" "1600,875.95" "1" "1" "180")
(command "_insert" "blkuc5" "1600,876.69" "1" "1" "0")
(command "_insert" "blkuc5" "1600,876.32" "1" "1" "180")
(command "_insert" "blkuc5" "1600,877.06" "1" "1" "0")
(command "_insert" "blkuc5" "1600,876.69" "1" "1" "180")
(command "_insert" "blkuc5" "1600,877.43" "1" "1" "0")
(command "_insert" "blkuc5" "1600,877.06" "1" "1" "180")
(command "_insert" "blkuc5" "1600,877.8" "1" "1" "0")
(command "_insert" "blkuc5" "1600,877.43" "1" "1" "180")
(command "_insert" "blkuc5" "1600,878.17" "1" "1" "0")
(command "_insert" "blkuc5" "1600,877.8" "1" "1" "180")
(command "_insert" "blkuc5" "1600,878.54" "1" "1" "0")
(command "_insert" "blkuc5" "1600,878.17" "1" "1" "180")
(command "_insert" "blkuc5" "1600,878.91" "1" "1" "0")
(command "_insert" "blkuc5" "1600,878.54" "1" "1" "180")
(command "_insert" "blkuc5" "1600,879.28" "1" "1" "0")
(command "_insert" "blkuc5" "1600,878.91" "1" "1" "180")
(command "_insert" "blkuc5" "1600,879.65" "1" "1" "0")
(command "_insert" "blkuc5" "1600,879.28" "1" "1" "180")
(command "_insert" "blkuc5" "1600,880.02" "1" "1" "0")
(command "_insert" "blkuc5" "1600,879.65" "1" "1" "180")
(command "_insert" "blkuc5" "1600,880.39" "1" "1" "0")
(command "_insert" "blkuc5" "1600,880.02" "1" "1" "180")
(command "_insert" "blkuc5" "1600,880.76" "1" "1" "0")
(command "_insert" "blkuc5" "1600,880.39" "1" "1" "180")
(command "_insert" "blkuc5" "1600,881.13" "1" "1" "0")
(command "_insert" "blkuc5" "1600,880.76" "1" "1" "180")
(command "_insert" "blkuc5" "1600,881.5" "1" "1" "0")
(command "_insert" "blkuc5" "1600,881.13" "1" "1" "180")
(command "_insert" "blkuc5" "1600,881.87" "1" "1" "0")
(command "_insert" "blkuc5" "1600,881.5" "1" "1" "180")
(command "_insert" "blkuc5" "1600,882.24" "1" "1" "0")
(command "_insert" "blkuc5" "1600,881.87" "1" "1" "180")
(command "_insert" "blkuc5" "1600,882.61" "1" "1" "0")
(command "_insert" "blkuc5" "1600,882.24" "1" "1" "180")
(command "_insert" "blkuc5" "1600,882.98" "1" "1" "0")
(command "_insert" "blkuc5" "1600,882.61" "1" "1" "180")
(command "_insert" "blkuc5" "1600,883.35" "1" "1" "0")
(command "_insert" "blkuc5" "1600,882.98" "1" "1" "180")
(command "_insert" "blkuc5" "1600,883.72" "1" "1" "0")
(command "_insert" "blkuc5" "1600,883.35" "1" "1" "180")
(command "_insert" "blkuc5" "1600,884.09" "1" "1" "0")
(command "_insert" "blkuc5" "1600,883.72" "1" "1" "180")
(command "_insert" "blkuc5" "1600,884.46" "1" "1" "0")
(command "_insert" "blkuc5" "1600,884.09" "1" "1" "180")
(command "_insert" "blkuc5" "1600,884.83" "1" "1" "0")
(command "_insert" "blkuc5" "1600,884.46" "1" "1" "180")
(command "_insert" "blkuc5" "1600,885.2" "1" "1" "0")
(command "_insert" "blkuc5" "1600,884.83" "1" "1" "180")
(command "_insert" "blkuc5" "1600,885.57" "1" "1" "0")
(command "_insert" "blkuc5" "1600,885.2" "1" "1" "180")
(command "_insert" "blkuc5" "1600,885.94" "1" "1" "0")
(command "_insert" "blkuc5" "1600,885.57" "1" "1" "180")
(command "_insert" "blkuc5" "1600,886.31" "1" "1" "0")
(command "_insert" "blkuc5" "1600,885.94" "1" "1" "180")
(command "_insert" "blkuc5" "1600,886.68" "1" "1" "0")
(command "_insert" "blkuc5" "1600,886.31" "1" "1" "180")
(command "_insert" "blkuc5" "1600,887.05" "1" "1" "0")
(command "_insert" "blkuc5" "1600,886.68" "1" "1" "180")
(command "_insert" "blkuc5" "1600,887.42" "1" "1" "0")
(command "_insert" "blkuc5" "1600,887.05" "1" "1" "180")
(command "_insert" "blkuc5" "1600,887.79" "1" "1" "0")
(command "_insert" "blkuc5" "1600,887.42" "1" "1" "180")
(command "_insert" "blkuc5" "1600,888.16" "1" "1" "0")
(command "_insert" "blkuc5" "1600,887.79" "1" "1" "180")
(command "_insert" "blkuc5" "1600,888.53" "1" "1" "0")
(command "_insert" "blkuc5" "1600,888.16" "1" "1" "180")
(command "_insert" "blkuc5" "1600,888.9" "1" "1" "0")
(command "_insert" "blkuc5" "1600,888.53" "1" "1" "180")
(command "_insert" "blkuc5" "1600,889.27" "1" "1" "0")
(command "_insert" "blkuc5" "1600,888.9" "1" "1" "180")
(command "_insert" "blkuc5" "1600,889.64" "1" "1" "0")
(command "_insert" "blkuc5" "1600,889.27" "1" "1" "180")
(command "_insert" "blkuc5" "1600,890.01" "1" "1" "0")
(command "_insert" "blkuc5" "1600,889.64" "1" "1" "180")
(command "_insert" "blkuc5" "1600,890.38" "1" "1" "0")
(command "_insert" "blkuc5" "1600,890.01" "1" "1" "180")
(command "_insert" "blkuc5" "1600,890.75" "1" "1" "0")
(command "_insert" "blkuc5" "1600,890.38" "1" "1" "180")
(command "_insert" "blkuc5" "1600,891.12" "1" "1" "0")
(command "_insert" "blkuc5" "1600,890.75" "1" "1" "180")
(command "_insert" "blkuc5" "1600,891.49" "1" "1" "0")
(command "_insert" "blkuc5" "1600,891.12" "1" "1" "180")
(command "_insert" "blkuc5" "1600,891.86" "1" "1" "0")
(command "_insert" "blkuc5" "1600,891.49" "1" "1" "180")
(command "_insert" "blkuc5" "1600,892.23" "1" "1" "0")
(command "_insert" "blkuc5" "1600,891.86" "1" "1" "180")
(command "_insert" "blkuc5" "1600,892.6" "1" "1" "0")
(command "_insert" "blkuc5" "1600,892.23" "1" "1" "180")
(command "_insert" "blkuc5" "1600,892.97" "1" "1" "0")
(command "_insert" "blkuc5" "1600,892.6" "1" "1" "180")
(command "_insert" "blkuc5" "1600,893.34" "1" "1" "0")
(command "_insert" "blkuc5" "1600,892.97" "1" "1" "180")
(command "_insert" "blkuc5" "1600,893.71" "1" "1" "0")
(command "_insert" "blkuc5" "1600,893.34" "1" "1" "180")
(command "_insert" "blkuc5" "1600,894.08" "1" "1" "0")
(command "_insert" "blkuc5" "1600,893.71" "1" "1" "180")
(command "_insert" "blkuc5" "1600,894.45" "1" "1" "0")
(command "_insert" "blkuc5" "1600,894.08" "1" "1" "180")
(command "_insert" "blkuc5" "1600,894.82" "1" "1" "0")
(command "_insert" "blkuc5" "1600,894.45" "1" "1" "180")
(command "_insert" "blkuc5" "1600,895.19" "1" "1" "0")
(command "_insert" "blkuc5" "1600,894.82" "1" "1" "180")
(command "_insert" "blkuc5" "1600,895.56" "1" "1" "0")
(command "_insert" "blkuc5" "1600,895.19" "1" "1" "180")
(command "_insert" "blkuc5" "1600,895.93" "1" "1" "0")
(command "_insert" "blkuc5" "1600,895.56" "1" "1" "180")
(command "_insert" "blkuc5" "1600,896.3" "1" "1" "0")
(command "_insert" "blkuc5" "1600,895.93" "1" "1" "180")
(command "_insert" "blkuc5" "1600,896.67" "1" "1" "0")
(command "_insert" "blkuc5" "1600,896.3" "1" "1" "180")
(command "_insert" "blkuc5" "1600,897.04" "1" "1" "0")
(command "_insert" "blkuc5" "1600,896.67" "1" "1" "180")
(command "_insert" "blkuc5" "1600,897.41" "1" "1" "0")
(command "_insert" "blkuc5" "1600,897.04" "1" "1" "180")
(command "_insert" "blkuc5" "1600,897.78" "1" "1" "0")
(command "_insert" "blkuc5" "1600,897.41" "1" "1" "180")
(command "_insert" "blkuc5" "1600,898.15" "1" "1" "0")
(command "_insert" "blkuc5" "1600,897.78" "1" "1" "180")
(command "_insert" "blkuc5" "1600,898.52" "1" "1" "0")
(command "_insert" "blkuc5" "1600,898.15" "1" "1" "180")
(command "_insert" "blkuc5" "1600,898.89" "1" "1" "0")
(command "_insert" "blkuc5" "1600,898.52" "1" "1" "180")
(command "_insert" "blkuc5" "1600,899.26" "1" "1" "0")
(command "_insert" "blkuc5" "1600,898.89" "1" "1" "180")
(command "_insert" "blkuc5" "1600,899.63" "1" "1" "0")
(command "_insert" "blkuc5" "1600,899.26" "1" "1" "180")
(command "_insert" "blkuc5" "1600,900" "1" "1" "0")
(command "_insert" "blkuc5" "1600,899.63" "1" "1" "180")
(command "_insert" "blkuc5" "1600,900.37" "1" "1" "0")
(command "_insert" "blkuc5" "1600,900" "1" "1" "180")
(command "_insert" "blkuc5" "1600,900.74" "1" "1" "0")
(command "_insert" "blkuc5" "1600,900.37" "1" "1" "180")
(command "_insert" "blkuc5" "1600,901.11" "1" "1" "0")
(command "_insert" "blkuc5" "1600,900.74" "1" "1" "180")
(command "_insert" "blkuc5" "1600,901.48" "1" "1" "0")
(command "_insert" "blkuc5" "1600,901.11" "1" "1" "180")
(command "_insert" "blkuc5" "1600,901.85" "1" "1" "0")
(command "_insert" "blkuc5" "1600,901.48" "1" "1" "180")
(command "_insert" "blkuc5" "1600,902.22" "1" "1" "0")
(command "_insert" "blkuc5" "1600,901.85" "1" "1" "180")
(command "_insert" "blkuc5" "1600,902.59" "1" "1" "0")
(command "_insert" "blkuc5" "1600,902.22" "1" "1" "180")
(command "_insert" "blkuc5" "1600,902.96" "1" "1" "0")
(command "_insert" "blkuc5" "1600,902.59" "1" "1" "180")
(command "_insert" "blkuc5" "1600,903.33" "1" "1" "0")
(command "_insert" "blkuc5" "1600,902.96" "1" "1" "180")
(command "_insert" "blkuc5" "1600,903.7" "1" "1" "0")
(command "_insert" "blkuc5" "1600,903.33" "1" "1" "180")
(command "_insert" "blkuc5" "1600,904.07" "1" "1" "0")
(command "_insert" "blkuc5" "1600,903.7" "1" "1" "180")
(command "_insert" "blkuc5" "1600,904.44" "1" "1" "0")
(command "_insert" "blkuc5" "1600,904.07" "1" "1" "180")
(command "_insert" "blkuc5" "1600,904.81" "1" "1" "0")
(command "_insert" "blkuc5" "1600,904.44" "1" "1" "180")
(command "_insert" "blkuc5" "1600,905.18" "1" "1" "0")
(command "_insert" "blkuc5" "1600,904.81" "1" "1" "180")
(command "_insert" "blkuc5" "1600,905.55" "1" "1" "0")
(command "_insert" "blkuc5" "1600,905.18" "1" "1" "180")
(command "_insert" "blkuc5" "1600,905.92" "1" "1" "0")
(command "_insert" "blkuc5" "1600,905.55" "1" "1" "180")
(command "_insert" "blkuc5" "1600,906.29" "1" "1" "0")
(command "_insert" "blkuc5" "1600,905.92" "1" "1" "180")
(command "_insert" "blkuc5" "1600,906.66" "1" "1" "0")
(command "_insert" "blkuc5" "1600,906.29" "1" "1" "180")
(command "_insert" "blkuc5" "1600,907.03" "1" "1" "0")
(command "_insert" "blkuc5" "1600,906.66" "1" "1" "180")
(command "_insert" "blkuc5" "1600,907.4" "1" "1" "0")
(command "_insert" "blkuc5" "1600,907.03" "1" "1" "180")
(command "_insert" "blkuc5" "1600,907.77" "1" "1" "0")
(command "_insert" "blkuc5" "1600,907.4" "1" "1" "180")
(command "_insert" "blkuc5" "1600,908.14" "1" "1" "0")
(command "_insert" "blkuc5" "1600,907.77" "1" "1" "180")
(command "_insert" "blkuc5" "1600,908.51" "1" "1" "0")
(command "_insert" "blkuc5" "1600,908.14" "1" "1" "180")
(command "_insert" "blkuc5" "1600,908.88" "1" "1" "0")
(command "_insert" "blkuc5" "1600,908.51" "1" "1" "180")
(command "_insert" "blkuc5" "1600,909.25" "1" "1" "0")
(command "_insert" "blkuc5" "1600,908.88" "1" "1" "180")
(command "_insert" "blkuc5" "1600,909.62" "1" "1" "0")
(command "_insert" "blkuc5" "1600,909.25" "1" "1" "180")
(command "_insert" "blkuc5" "1600,909.99" "1" "1" "0")
(command "_insert" "blkuc5" "1600,909.62" "1" "1" "180")
(command "_insert" "blkuc5" "1600,910.36" "1" "1" "0")
(command "_insert" "blkuc5" "1600,909.99" "1" "1" "180")
(command "_insert" "blkuc5" "1600,910.73" "1" "1" "0")
(command "_insert" "blkuc5" "1600,910.36" "1" "1" "180")
(command "_insert" "blkuc5" "1600,911.1" "1" "1" "0")
(command "_insert" "blkuc5" "1600,910.73" "1" "1" "180")
(command "_insert" "blkuc5" "1600,911.47" "1" "1" "0")
(command "_insert" "blkuc5" "1600,911.1" "1" "1" "180")
(command "_insert" "blkuc5" "1600,911.84" "1" "1" "0")
(command "_insert" "blkuc5" "1600,911.47" "1" "1" "180")
(command "_insert" "blkuc5" "1600,912.21" "1" "1" "0")
(command "_insert" "blkuc5" "1600,911.84" "1" "1" "180")
(command "_insert" "blkuc5" "1600,912.58" "1" "1" "0")
(command "_insert" "blkuc5" "1600,912.21" "1" "1" "180")
(command "_insert" "blkuc5" "1600,912.95" "1" "1" "0")
(command "_insert" "blkuc5" "1600,912.58" "1" "1" "180")
(command "_insert" "blkuc5" "1600,913.32" "1" "1" "0")
(command "_insert" "blkuc5" "1600,912.95" "1" "1" "180")
(command "_insert" "blkuc5" "1600,913.69" "1" "1" "0")
(command "_insert" "blkuc5" "1600,913.32" "1" "1" "180")
(command "_insert" "blkuc5" "1600,914.06" "1" "1" "0")
(command "_insert" "blkuc5" "1600,913.69" "1" "1" "180")
(command "_insert" "blkuc5" "1600,914.43" "1" "1" "0")
(command "_insert" "blkuc5" "1600,914.06" "1" "1" "180")
(command "_insert" "blkuc5" "1600,914.8" "1" "1" "0")
(command "_insert" "blkuc5" "1600,914.43" "1" "1" "180")
(command "_insert" "blkuc5" "1600,915.17" "1" "1" "0")
(command "_insert" "blkuc5" "1600,914.8" "1" "1" "180")
(command "_insert" "blkuc5" "1600,915.54" "1" "1" "0")
(command "_insert" "blkuc5" "1600,915.17" "1" "1" "180")
(command "_insert" "blkuc5" "1600,915.91" "1" "1" "0")
(command "_insert" "blkuc5" "1600,915.54" "1" "1" "180")
(command "_insert" "blkuc5" "1600,916.28" "1" "1" "0")
(command "_insert" "blkuc5" "1600,915.91" "1" "1" "180")
(command "_insert" "blkuc5" "1600,916.65" "1" "1" "0")
(command "_insert" "blkuc5" "1600,916.28" "1" "1" "180")
(command "_insert" "blkuc5" "1600,917.02" "1" "1" "0")
(command "_insert" "blkuc5" "1600,916.65" "1" "1" "180")
(command "_insert" "blkuc5" "1600,917.39" "1" "1" "0")
(command "_insert" "blkuc5" "1600,917.02" "1" "1" "180")
(command "_insert" "blkuc5" "1600,917.76" "1" "1" "0")
(command "_insert" "blkuc5" "1600,917.39" "1" "1" "180")
(command "_insert" "blkuc5" "1600,918.13" "1" "1" "0")
(command "_insert" "blkuc5" "1600,917.76" "1" "1" "180")
(command "_insert" "blkuc5" "1600,918.5" "1" "1" "0")
(command "_insert" "blkuc5" "1600,918.13" "1" "1" "180")
(command "_insert" "blkuc5" "1600,918.87" "1" "1" "0")
(command "_insert" "blkuc5" "1600,918.5" "1" "1" "180")
(command "_insert" "blkuc5" "1600,919.24" "1" "1" "0")
(command "_insert" "blkuc5" "1600,918.87" "1" "1" "180")
(command "_insert" "blkuc5" "1600,919.61" "1" "1" "0")
(command "_insert" "blkuc5" "1600,919.24" "1" "1" "180")
(command "_insert" "blkuc5" "1600,919.98" "1" "1" "0")
(command "_insert" "blkuc5" "1600,919.61" "1" "1" "180")
(command "_insert" "blkuc5" "1600,920.35" "1" "1" "0")
(command "_insert" "blkuc5" "1600,919.98" "1" "1" "180")
(command "_insert" "blkuc5" "1600,920.72" "1" "1" "0")
(command "_insert" "blkuc5" "1600,920.35" "1" "1" "180")
(command "_insert" "blkuc5" "1600,921.09" "1" "1" "0")
(command "_insert" "blkuc5" "1600,920.72" "1" "1" "180")
(command "_insert" "blkuc5" "1600,921.46" "1" "1" "0")
(command "_insert" "blkuc5" "1600,921.09" "1" "1" "180")
(command "_insert" "blkuc5" "1600,921.83" "1" "1" "0")
(command "_insert" "blkuc5" "1600,921.46" "1" "1" "180")
(command "_insert" "blkuc5" "1600,922.2" "1" "1" "0")
(command "_insert" "blkuc5" "1600,921.83" "1" "1" "180")
(command "_insert" "blkuc5" "1600,922.57" "1" "1" "0")
(command "_insert" "blkuc5" "1600,922.2" "1" "1" "180")
(command "_insert" "blkuc5" "1600,922.94" "1" "1" "0")
(command "_insert" "blkuc5" "1600,922.57" "1" "1" "180")
(command "_insert" "blkuc5" "1600,923.31" "1" "1" "0")
(command "_insert" "blkuc5" "1600,922.94" "1" "1" "180")
(command "_insert" "blkuc5" "1600,923.68" "1" "1" "0")
(command "_insert" "blkuc5" "1600,923.31" "1" "1" "180")
(command "_insert" "blkuc5" "1600,924.05" "1" "1" "0")
(command "_insert" "blkuc5" "1600,923.68" "1" "1" "180")
(command "_insert" "blkuc5" "1600,924.42" "1" "1" "0")
(command "_insert" "blkuc5" "1600,924.05" "1" "1" "180")
(command "_insert" "blkuc5" "1600,924.79" "1" "1" "0")
(command "_insert" "blkuc5" "1600,924.42" "1" "1" "180")
(command "_insert" "blkuc5" "1600,925.16" "1" "1" "0")
(command "_insert" "blkuc5" "1600,924.79" "1" "1" "180")
(command "_insert" "blkuc5" "1600,925.53" "1" "1" "0")
(command "_insert" "blkuc5" "1600,925.16" "1" "1" "180")
(command "_insert" "blkuc5" "1600,925.9" "1" "1" "0")
(command "_insert" "blkuc5" "1600,925.53" "1" "1" "180")
(command "_insert" "blkuc5" "1600,926.27" "1" "1" "0")
(command "_insert" "blkuc5" "1600,925.9" "1" "1" "180")
(command "_insert" "blkuc5" "1600,926.64" "1" "1" "0")
(command "_insert" "blkuc5" "1600,926.27" "1" "1" "180")
(command "_insert" "blkuc5" "1600,927.01" "1" "1" "0")
(command "_insert" "blkuc5" "1600,926.64" "1" "1" "180")
(command "_insert" "blkuc5" "1600,927.38" "1" "1" "0")
(command "_insert" "blkuc5" "1600,927.01" "1" "1" "180")
(command "_insert" "blkuc5" "1600,927.75" "1" "1" "0")
(command "_insert" "blkuc5" "1600,927.38" "1" "1" "180")
(command "_layer" "set" "phccover" "")
(command "_rectangle" "1598.908,933.3" "1601.092,866.7")
(command "_layer" "set" "nitride" "")
(setq phc5 currobj)
(command "_layer" "set" "cover" "")
(command "_rectangle" "1598.908,836.7" "1601.092,963.3")
(command "_layer" "set" "nitride" "")
(command "_layer" "set" "text" "")
(command "_circle" "1597.958,846.7" "0.075")
(command "_circle" "1597.583,846.7" "0.15")
(command "_circle" "1597.208,846.7" "0.075")
(command "_circle" "1596.833,846.7" "0.15")
(command "_circle" "1597.958,848.7" "0.075")
(command "_circle" "1597.583,848.7" "0.075")
(command "_circle" "1597.208,848.7" "0.15")
(command "_circle" "1596.833,848.7" "0.15")
(command "_circle" "1597.958,850.7" "0.075")
(command "_circle" "1597.583,850.7" "0.15")
(command "_circle" "1597.208,850.7" "0.15")
(command "_circle" "1596.833,850.7" "0.15")
(command "_circle" "1597.958,852.7" "0.075")
(command "_circle" "1597.583,852.7" "0.075")
(command "_circle" "1597.208,852.7" "0.075")
(command "_circle" "1596.833,852.7" "0.075")
(command "_circle" "1596.458,852.7" "0.15")
(command "_circle" "1597.958,854.7" "0.075")
(command "_circle" "1597.583,854.7" "0.15")
(command "_circle" "1597.208,854.7" "0.075")
(command "_circle" "1596.833,854.7" "0.075")
(command "_circle" "1596.458,854.7" "0.15")
(command "_circle" "1597.958,856.7" "0.075")
(command "_circle" "1597.583,856.7" "0.075")
(command "_circle" "1597.208,856.7" "0.15")
(command "_circle" "1596.833,856.7" "0.075")
(command "_circle" "1596.458,856.7" "0.15")
(command "_circle" "1597.958,858.7" "0.075")
(command "_circle" "1597.583,858.7" "0.15")
(command "_circle" "1597.208,858.7" "0.15")
(command "_circle" "1596.833,858.7" "0.075")
(command "_circle" "1596.458,858.7" "0.15")
(command "_circle" "1597.958,860.7" "0.075")
(command "_circle" "1597.583,860.7" "0.075")
(command "_circle" "1597.208,860.7" "0.075")
(command "_circle" "1596.833,860.7" "0.15")
(command "_circle" "1596.458,860.7" "0.15")
(command "_circle" "1597.958,862.7" "0.075")
(command "_circle" "1597.583,862.7" "0.15")
(command "_circle" "1597.208,862.7" "0.075")
(command "_circle" "1596.833,862.7" "0.15")
(command "_circle" "1596.458,862.7" "0.15")
(command "_circle" "1597.958,864.7" "0.075")
(command "_circle" "1597.583,864.7" "0.075")
(command "_circle" "1597.208,864.7" "0.15")
(command "_circle" "1596.833,864.7" "0.15")
(command "_circle" "1596.458,864.7" "0.15")
(command "_circle" "1597.958,866.7" "0.075")
(command "_circle" "1597.583,866.7" "0.15")
(command "_circle" "1597.208,866.7" "0.15")
(command "_circle" "1596.833,866.7" "0.15")
(command "_circle" "1596.458,866.7" "0.15")
(command "_circle" "1597.958,868.7" "0.075")
(command "_circle" "1597.583,868.7" "0.075")
(command "_circle" "1597.208,868.7" "0.075")
(command "_circle" "1596.833,868.7" "0.075")
(command "_circle" "1596.458,868.7" "0.075")
(command "_circle" "1596.083,868.7" "0.15")
(command "_circle" "1597.958,870.7" "0.075")
(command "_circle" "1597.583,870.7" "0.15")
(command "_circle" "1597.208,870.7" "0.075")
(command "_circle" "1596.833,870.7" "0.075")
(command "_circle" "1596.458,870.7" "0.075")
(command "_circle" "1596.083,870.7" "0.15")
(command "_circle" "1597.958,872.7" "0.075")
(command "_circle" "1597.583,872.7" "0.075")
(command "_circle" "1597.208,872.7" "0.15")
(command "_circle" "1596.833,872.7" "0.075")
(command "_circle" "1596.458,872.7" "0.075")
(command "_circle" "1596.083,872.7" "0.15")
(command "_circle" "1597.958,874.7" "0.075")
(command "_circle" "1597.583,874.7" "0.15")
(command "_circle" "1597.208,874.7" "0.15")
(command "_circle" "1596.833,874.7" "0.075")
(command "_circle" "1596.458,874.7" "0.075")
(command "_circle" "1596.083,874.7" "0.15")
(command "_circle" "1597.958,876.7" "0.075")
(command "_circle" "1597.583,876.7" "0.075")
(command "_circle" "1597.208,876.7" "0.075")
(command "_circle" "1596.833,876.7" "0.15")
(command "_circle" "1596.458,876.7" "0.075")
(command "_circle" "1596.083,876.7" "0.15")
(command "_circle" "1597.958,878.7" "0.075")
(command "_circle" "1597.583,878.7" "0.15")
(command "_circle" "1597.208,878.7" "0.075")
(command "_circle" "1596.833,878.7" "0.15")
(command "_circle" "1596.458,878.7" "0.075")
(command "_circle" "1596.083,878.7" "0.15")
(command "_circle" "1597.958,880.7" "0.075")
(command "_circle" "1597.583,880.7" "0.075")
(command "_circle" "1597.208,880.7" "0.15")
(command "_circle" "1596.833,880.7" "0.15")
(command "_circle" "1596.458,880.7" "0.075")
(command "_circle" "1596.083,880.7" "0.15")
(command "_circle" "1597.958,882.7" "0.075")
(command "_circle" "1597.583,882.7" "0.15")
(command "_circle" "1597.208,882.7" "0.15")
(command "_circle" "1596.833,882.7" "0.15")
(command "_circle" "1596.458,882.7" "0.075")
(command "_circle" "1596.083,882.7" "0.15")
(command "_circle" "1597.958,884.7" "0.075")
(command "_circle" "1597.583,884.7" "0.075")
(command "_circle" "1597.208,884.7" "0.075")
(command "_circle" "1596.833,884.7" "0.075")
(command "_circle" "1596.458,884.7" "0.15")
(command "_circle" "1596.083,884.7" "0.15")
(command "_circle" "1597.958,886.7" "0.075")
(command "_circle" "1597.583,886.7" "0.15")
(command "_circle" "1597.208,886.7" "0.075")
(command "_circle" "1596.833,886.7" "0.075")
(command "_circle" "1596.458,886.7" "0.15")
(command "_circle" "1596.083,886.7" "0.15")
(command "_circle" "1597.958,888.7" "0.075")
(command "_circle" "1597.583,888.7" "0.075")
(command "_circle" "1597.208,888.7" "0.15")
(command "_circle" "1596.833,888.7" "0.075")
(command "_circle" "1596.458,888.7" "0.15")
(command "_circle" "1596.083,888.7" "0.15")
(command "_circle" "1597.958,890.7" "0.075")
(command "_circle" "1597.583,890.7" "0.15")
(command "_circle" "1597.208,890.7" "0.15")
(command "_circle" "1596.833,890.7" "0.075")
(command "_circle" "1596.458,890.7" "0.15")
(command "_circle" "1596.083,890.7" "0.15")
(command "_circle" "1597.958,892.7" "0.075")
(command "_circle" "1597.583,892.7" "0.075")
(command "_circle" "1597.208,892.7" "0.075")
(command "_circle" "1596.833,892.7" "0.15")
(command "_circle" "1596.458,892.7" "0.15")
(command "_circle" "1596.083,892.7" "0.15")
(command "_circle" "1597.958,894.7" "0.075")
(command "_circle" "1597.583,894.7" "0.15")
(command "_circle" "1597.208,894.7" "0.075")
(command "_circle" "1596.833,894.7" "0.15")
(command "_circle" "1596.458,894.7" "0.15")
(command "_circle" "1596.083,894.7" "0.15")
(command "_circle" "1597.958,896.7" "0.075")
(command "_circle" "1597.583,896.7" "0.075")
(command "_circle" "1597.208,896.7" "0.15")
(command "_circle" "1596.833,896.7" "0.15")
(command "_circle" "1596.458,896.7" "0.15")
(command "_circle" "1596.083,896.7" "0.15")
(command "_circle" "1597.958,898.7" "0.075")
(command "_circle" "1597.583,898.7" "0.15")
(command "_circle" "1597.208,898.7" "0.15")
(command "_circle" "1596.833,898.7" "0.15")
(command "_circle" "1596.458,898.7" "0.15")
(command "_circle" "1596.083,898.7" "0.15")
(command "_circle" "1597.958,900.7" "0.075")
(command "_circle" "1597.583,900.7" "0.075")
(command "_circle" "1597.208,900.7" "0.075")
(command "_circle" "1596.833,900.7" "0.075")
(command "_circle" "1596.458,900.7" "0.075")
(command "_circle" "1596.083,900.7" "0.075")
(command "_circle" "1595.708,900.7" "0.15")
(command "_circle" "1597.958,902.7" "0.075")
(command "_circle" "1597.583,902.7" "0.15")
(command "_circle" "1597.208,902.7" "0.075")
(command "_circle" "1596.833,902.7" "0.075")
(command "_circle" "1596.458,902.7" "0.075")
(command "_circle" "1596.083,902.7" "0.075")
(command "_circle" "1595.708,902.7" "0.15")
(command "_circle" "1597.958,904.7" "0.075")
(command "_circle" "1597.583,904.7" "0.075")
(command "_circle" "1597.208,904.7" "0.15")
(command "_circle" "1596.833,904.7" "0.075")
(command "_circle" "1596.458,904.7" "0.075")
(command "_circle" "1596.083,904.7" "0.075")
(command "_circle" "1595.708,904.7" "0.15")
(command "_circle" "1597.958,906.7" "0.075")
(command "_circle" "1597.583,906.7" "0.15")
(command "_circle" "1597.208,906.7" "0.15")
(command "_circle" "1596.833,906.7" "0.075")
(command "_circle" "1596.458,906.7" "0.075")
(command "_circle" "1596.083,906.7" "0.075")
(command "_circle" "1595.708,906.7" "0.15")
(command "_circle" "1597.958,908.7" "0.075")
(command "_circle" "1597.583,908.7" "0.075")
(command "_circle" "1597.208,908.7" "0.075")
(command "_circle" "1596.833,908.7" "0.15")
(command "_circle" "1596.458,908.7" "0.075")
(command "_circle" "1596.083,908.7" "0.075")
(command "_circle" "1595.708,908.7" "0.15")
(command "_circle" "1597.958,910.7" "0.075")
(command "_circle" "1597.583,910.7" "0.15")
(command "_circle" "1597.208,910.7" "0.075")
(command "_circle" "1596.833,910.7" "0.15")
(command "_circle" "1596.458,910.7" "0.075")
(command "_circle" "1596.083,910.7" "0.075")
(command "_circle" "1595.708,910.7" "0.15")
(command "_circle" "1597.958,912.7" "0.075")
(command "_circle" "1597.583,912.7" "0.075")
(command "_circle" "1597.208,912.7" "0.15")
(command "_circle" "1596.833,912.7" "0.15")
(command "_circle" "1596.458,912.7" "0.075")
(command "_circle" "1596.083,912.7" "0.075")
(command "_circle" "1595.708,912.7" "0.15")
(command "_circle" "1597.958,914.7" "0.075")
(command "_circle" "1597.583,914.7" "0.15")
(command "_circle" "1597.208,914.7" "0.15")
(command "_circle" "1596.833,914.7" "0.15")
(command "_circle" "1596.458,914.7" "0.075")
(command "_circle" "1596.083,914.7" "0.075")
(command "_circle" "1595.708,914.7" "0.15")
(command "_circle" "1597.958,916.7" "0.075")
(command "_circle" "1597.583,916.7" "0.075")
(command "_circle" "1597.208,916.7" "0.075")
(command "_circle" "1596.833,916.7" "0.075")
(command "_circle" "1596.458,916.7" "0.15")
(command "_circle" "1596.083,916.7" "0.075")
(command "_circle" "1595.708,916.7" "0.15")
(command "_circle" "1597.958,918.7" "0.075")
(command "_circle" "1597.583,918.7" "0.15")
(command "_circle" "1597.208,918.7" "0.075")
(command "_circle" "1596.833,918.7" "0.075")
(command "_circle" "1596.458,918.7" "0.15")
(command "_circle" "1596.083,918.7" "0.075")
(command "_circle" "1595.708,918.7" "0.15")
(command "_circle" "1597.958,920.7" "0.075")
(command "_circle" "1597.583,920.7" "0.075")
(command "_circle" "1597.208,920.7" "0.15")
(command "_circle" "1596.833,920.7" "0.075")
(command "_circle" "1596.458,920.7" "0.15")
(command "_circle" "1596.083,920.7" "0.075")
(command "_circle" "1595.708,920.7" "0.15")
(command "_circle" "1597.958,922.7" "0.075")
(command "_circle" "1597.583,922.7" "0.15")
(command "_circle" "1597.208,922.7" "0.15")
(command "_circle" "1596.833,922.7" "0.075")
(command "_circle" "1596.458,922.7" "0.15")
(command "_circle" "1596.083,922.7" "0.075")
(command "_circle" "1595.708,922.7" "0.15")
(command "_circle" "1597.958,924.7" "0.075")
(command "_circle" "1597.583,924.7" "0.075")
(command "_circle" "1597.208,924.7" "0.075")
(command "_circle" "1596.833,924.7" "0.15")
(command "_circle" "1596.458,924.7" "0.15")
(command "_circle" "1596.083,924.7" "0.075")
(command "_circle" "1595.708,924.7" "0.15")
(command "_circle" "1597.958,926.7" "0.075")
(command "_circle" "1597.583,926.7" "0.15")
(command "_circle" "1597.208,926.7" "0.075")
(command "_circle" "1596.833,926.7" "0.15")
(command "_circle" "1596.458,926.7" "0.15")
(command "_circle" "1596.083,926.7" "0.075")
(command "_circle" "1595.708,926.7" "0.15")
(command "_circle" "1597.958,928.7" "0.075")
(command "_circle" "1597.583,928.7" "0.075")
(command "_circle" "1597.208,928.7" "0.15")
(command "_circle" "1596.833,928.7" "0.15")
(command "_circle" "1596.458,928.7" "0.15")
(command "_circle" "1596.083,928.7" "0.075")
(command "_circle" "1595.708,928.7" "0.15")
(command "_circle" "1597.958,930.7" "0.075")
(command "_circle" "1597.583,930.7" "0.15")
(command "_circle" "1597.208,930.7" "0.15")
(command "_circle" "1596.833,930.7" "0.15")
(command "_circle" "1596.458,930.7" "0.15")
(command "_circle" "1596.083,930.7" "0.075")
(command "_circle" "1595.708,930.7" "0.15")
(command "_circle" "1597.958,932.7" "0.075")
(command "_circle" "1597.583,932.7" "0.075")
(command "_circle" "1597.208,932.7" "0.075")
(command "_circle" "1596.833,932.7" "0.075")
(command "_circle" "1596.458,932.7" "0.075")
(command "_circle" "1596.083,932.7" "0.15")
(command "_circle" "1595.708,932.7" "0.15")
(command "_circle" "1597.958,934.7" "0.075")
(command "_circle" "1597.583,934.7" "0.15")
(command "_circle" "1597.208,934.7" "0.075")
(command "_circle" "1596.833,934.7" "0.075")
(command "_circle" "1596.458,934.7" "0.075")
(command "_circle" "1596.083,934.7" "0.15")
(command "_circle" "1595.708,934.7" "0.15")
(command "_circle" "1597.958,936.7" "0.075")
(command "_circle" "1597.583,936.7" "0.075")
(command "_circle" "1597.208,936.7" "0.15")
(command "_circle" "1596.833,936.7" "0.075")
(command "_circle" "1596.458,936.7" "0.075")
(command "_circle" "1596.083,936.7" "0.15")
(command "_circle" "1595.708,936.7" "0.15")
(command "_circle" "1597.958,938.7" "0.075")
(command "_circle" "1597.583,938.7" "0.15")
(command "_circle" "1597.208,938.7" "0.15")
(command "_circle" "1596.833,938.7" "0.075")
(command "_circle" "1596.458,938.7" "0.075")
(command "_circle" "1596.083,938.7" "0.15")
(command "_circle" "1595.708,938.7" "0.15")
(command "_circle" "1597.958,940.7" "0.075")
(command "_circle" "1597.583,940.7" "0.075")
(command "_circle" "1597.208,940.7" "0.075")
(command "_circle" "1596.833,940.7" "0.15")
(command "_circle" "1596.458,940.7" "0.075")
(command "_circle" "1596.083,940.7" "0.15")
(command "_circle" "1595.708,940.7" "0.15")
(command "_circle" "1597.958,942.7" "0.075")
(command "_circle" "1597.583,942.7" "0.15")
(command "_circle" "1597.208,942.7" "0.075")
(command "_circle" "1596.833,942.7" "0.15")
(command "_circle" "1596.458,942.7" "0.075")
(command "_circle" "1596.083,942.7" "0.15")
(command "_circle" "1595.708,942.7" "0.15")
(command "_circle" "1597.958,944.7" "0.075")
(command "_circle" "1597.583,944.7" "0.075")
(command "_circle" "1597.208,944.7" "0.15")
(command "_circle" "1596.833,944.7" "0.15")
(command "_circle" "1596.458,944.7" "0.075")
(command "_circle" "1596.083,944.7" "0.15")
(command "_circle" "1595.708,944.7" "0.15")
(command "_circle" "1597.958,946.7" "0.075")
(command "_circle" "1597.583,946.7" "0.15")
(command "_circle" "1597.208,946.7" "0.15")
(command "_circle" "1596.833,946.7" "0.15")
(command "_circle" "1596.458,946.7" "0.075")
(command "_circle" "1596.083,946.7" "0.15")
(command "_circle" "1595.708,946.7" "0.15")
(command "_circle" "1597.958,948.7" "0.075")
(command "_circle" "1597.583,948.7" "0.075")
(command "_circle" "1597.208,948.7" "0.075")
(command "_circle" "1596.833,948.7" "0.075")
(command "_circle" "1596.458,948.7" "0.15")
(command "_circle" "1596.083,948.7" "0.15")
(command "_circle" "1595.708,948.7" "0.15")
(command "_circle" "1597.958,950.7" "0.075")
(command "_circle" "1597.583,950.7" "0.15")
(command "_circle" "1597.208,950.7" "0.075")
(command "_circle" "1596.833,950.7" "0.075")
(command "_circle" "1596.458,950.7" "0.15")
(command "_circle" "1596.083,950.7" "0.15")
(command "_circle" "1595.708,950.7" "0.15")
(command "_circle" "1597.958,952.7" "0.075")
(command "_circle" "1597.583,952.7" "0.075")
(command "_circle" "1597.208,952.7" "0.15")
(command "_circle" "1596.833,952.7" "0.075")
(command "_circle" "1596.458,952.7" "0.15")
(command "_circle" "1596.083,952.7" "0.15")
(command "_circle" "1595.708,952.7" "0.15")
(command "_circle" "1597.958,954.7" "0.075")
(command "_circle" "1597.583,954.7" "0.15")
(command "_circle" "1597.208,954.7" "0.15")
(command "_circle" "1596.833,954.7" "0.075")
(command "_circle" "1596.458,954.7" "0.15")
(command "_circle" "1596.083,954.7" "0.15")
(command "_circle" "1595.708,954.7" "0.15")
(command "_circle" "1597.958,956.7" "0.075")
(command "_circle" "1597.583,956.7" "0.075")
(command "_circle" "1597.208,956.7" "0.075")
(command "_circle" "1596.833,956.7" "0.15")
(command "_circle" "1596.458,956.7" "0.15")
(command "_circle" "1596.083,956.7" "0.15")
(command "_circle" "1595.708,956.7" "0.15")
(command "_circle" "1597.958,958.7" "0.075")
(command "_circle" "1597.583,958.7" "0.15")
(command "_circle" "1597.208,958.7" "0.075")
(command "_circle" "1596.833,958.7" "0.15")
(command "_circle" "1596.458,958.7" "0.15")
(command "_circle" "1596.083,958.7" "0.15")
(command "_circle" "1595.708,958.7" "0.15")
(command "_circle" "1597.958,960.7" "0.075")
(command "_circle" "1597.583,960.7" "0.075")
(command "_circle" "1597.208,960.7" "0.15")
(command "_circle" "1596.833,960.7" "0.15")
(command "_circle" "1596.458,960.7" "0.15")
(command "_circle" "1596.083,960.7" "0.15")
(command "_circle" "1595.708,960.7" "0.15")
(command "_circle" "1597.958,962.7" "0.075")
(command "_circle" "1597.583,962.7" "0.15")
(command "_circle" "1597.208,962.7" "0.15")
(command "_circle" "1596.833,962.7" "0.15")
(command "_circle" "1596.458,962.7" "0.15")
(command "_circle" "1596.083,962.7" "0.15")
(command "_circle" "1595.708,962.7" "0.15")
(command "_layer" "set" "nitride" "")
(command "_layer" "set" "text" "")
(command-s "_text" "1586.908,963.3" "2" "-90" "a = 370 nm" )
(sssetfirst nil (ssget "_L"))
(if (not (numberp (vl-string-search "Mac" (getvar "platform")))) (c:txtexp))
(command "_layer" "set" "nitride" "")
(command "_layer" "set" "text" "")
(command-s "_text" "1583.908,963.3" "2" "-90" "gap = 250 nm" )
(sssetfirst nil (ssget "_L"))
(if (not (numberp (vl-string-search "Mac" (getvar "platform")))) (c:txtexp))
(command "_layer" "set" "nitride" "")
(command "_layer" "set" "text" "")
(command-s "_text" "1580.908,963.3" "2" "-90" "amplitude = 127 nm" )
(sssetfirst nil (ssget "_L"))
(if (not (numberp (vl-string-search "Mac" (getvar "platform")))) (c:txtexp))
(command "_layer" "set" "nitride" "")
(command "_layer" "set" "text" "")
(command-s "_text" "1577.908,963.3" "2" "-90" "start width = 280 nm" )
(sssetfirst nil (ssget "_L"))
(if (not (numberp (vl-string-search "Mac" (getvar "platform")))) (c:txtexp))
(command "_layer" "set" "nitride" "")
(command "_layer" "set" "text" "")
(command-s "_text" "1574.908,963.3" "2" "-90" "width = 294 nm" )
(sssetfirst nil (ssget "_L"))
(if (not (numberp (vl-string-search "Mac" (getvar "platform")))) (c:txtexp))
(command "_layer" "set" "nitride" "")
(command "_layer" "set" "text" "")
(command-s "_text" "1571.908,963.3" "2" "-90" "taper: 15" )
(sssetfirst nil (ssget "_L"))
(if (not (numberp (vl-string-search "Mac" (getvar "platform")))) (c:txtexp))
(command "_layer" "set" "nitride" "")
(command "_layer" "set" "text" "")
(command-s "_text" "1568.908,963.3" "2" "-90" "nominal: 150" )
(sssetfirst nil (ssget "_L"))
(if (not (numberp (vl-string-search "Mac" (getvar "platform")))) (c:txtexp))
(command "_layer" "set" "nitride" "")
(command "_layer" "set" "indicators" "")
(setq coords (list 
(list 1520.415 940) 
(list 1520.415 920) 
(list 1500.415 900) 
(list 1520.415 880) 
(list 1520.415 860) 
(list 1520.415 900) 
(list 1520.415 887.0711) 
(list 1507.4861 900) 
(list 1520.415 912.9289) 
(list 1520.415 900)))
(apply 'command (append '("pline") coords '("c")))
(command "._fillet" "radius" "1" "._fillet" "P" (entlast))
(setq coords (list 
(list 1679.585 940) 
(list 1679.585 920) 
(list 1699.585 900) 
(list 1679.585 880) 
(list 1679.585 860) 
(list 1679.585 900) 
(list 1679.585 887.0711) 
(list 1692.5139 900) 
(list 1679.585 912.9289) 
(list 1679.585 900)))
(apply 'command (append '("pline") coords '("c")))
(command "._fillet" "radius" "1" "._fillet" "P" (entlast))
(command "_layer" "set" "holes" "")
(command "_circle" "1518.0629,914.1124" "0.5")
(command "_circle" "1515.7109,911.7603" "0.5")
(command "_circle" "1513.3588,909.4083" "0.5")
(command "_circle" "1511.0067,907.0562" "0.5")
(command "_circle" "1508.6547,904.7041" "0.5")
(command "_circle" "1506.3026,902.3521" "0.5")
(command "_circle" "1503.9505,900" "0.5")
(command "_circle" "1506.3026,897.6479" "0.5")
(command "_circle" "1508.6547,895.2959" "0.5")
(command "_circle" "1511.0067,892.9438" "0.5")
(command "_circle" "1513.3588,890.5917" "0.5")
(command "_circle" "1515.7109,888.2397" "0.5")
(command "_circle" "1518.0629,885.8876" "0.5")
(command "_circle" "1681.9371,914.1124" "0.5")
(command "_circle" "1684.2891,911.7603" "0.5")
(command "_circle" "1686.6412,909.4083" "0.5")
(command "_circle" "1688.9933,907.0562" "0.5")
(command "_circle" "1691.3453,904.7041" "0.5")
(command "_circle" "1693.6974,902.3521" "0.5")
(command "_circle" "1696.0495,900" "0.5")
(command "_circle" "1693.6974,897.6479" "0.5")
(command "_circle" "1691.3453,895.2959" "0.5")
(command "_circle" "1688.9933,892.9438" "0.5")
(command "_circle" "1686.6412,890.5917" "0.5")
(command "_circle" "1684.2891,888.2397" "0.5")
(command "_circle" "1681.9371,885.8876" "0.5")
(command "_layer" "set" "nitride" "")
(command "_block" "blkcoupler5" "1600,900" coupler5 "")
(command "_insert" "blkcoupler5" "1600,900" "1" "1" "0")
(command "_insert" "blkcoupler5" "1600,900" "1" "1" "180")
(command "_block" "blksinglenanobeam5" "1600,900" singlenanobeam5 "")
(command "_insert" "blksinglenanobeam5" "1600,900" "1" "1" "0")
(command "_insert" "blksinglenanobeam5" "1600,900" "1" "1" "180")
(command "_block" "blkanglednodearray5" "1600,900" anglednodearray5 "")
(command "_insert" "blkanglednodearray5" "1600,900" "1" "1" "0")
(command "_insert" "blkanglednodearray5" "1600,900" "1" "1" "180")
(command "_block" "blkcooledsinglenanobeam5" "1600,900" cooledsinglenanobeam5 "")
(command "_insert" "blkcooledsinglenanobeam5" "1600,900" "1" "1" "0")
(command "_insert" "blkcooledsinglenanobeam5" "1600,900" "1" "1" "180")
(command "_block" "blkyjunction5" "1600,900" yjunction5 "")
(command "_insert" "blkyjunction5" "1600,900" "1" "1" "0")
(command "_insert" "blkyjunction5" "1600,900" "1" "1" "180")
; DRAWING BULGING VEE GROOVE
(command "_layer" "set" "vgroove" "")
(setq coords (list 
(list 1525.415 -605) 
(list 1525.415 0) 
(list 1525.415 0) 
(list 1525.415 1800) 
(list 1525.415 1800) 
(list 1525.415 2405) 
(list 1674.585 2405) 
(list 1674.585 1800) 
(list 1674.585 1800) 
(list 1674.585 0) 
(list 1674.585 0) 
(list 1674.585 -605)))
(apply 'command (append '("pline") coords '("c")))
(command "._fillet" "radius" "0" "._fillet" "P" (entlast))
(command "_layer" "set" "window" "")
(command "_rectangle" "1525.415,-1935" "1674.585,-600")
(command "_rectangle" "1525.415,2400" "1674.585,5300")
(command "_layer" "set" "grid" "")
(command "_rectangle" "1526.415,-1934" "1549.9433,-1909.2133")
(command "_array" "last" "" "R" "75" "3" "25.7867" "24.5283")
(command "_rectangle" "1601,-1934" "1624.5283,-1909.2133")
(command "_array" "last" "" "R" "75" "3" "25.7867" "24.5283")
(command "_rectangle" "1526.415,1" "1549.9433,25.7")
(command "_array" "last" "" "R" "70" "3" "25.7" "24.5283")
(command "_rectangle" "1601,1" "1624.5283,25.7")
(command "_array" "last" "" "R" "70" "3" "25.7" "24.5283")
(command "_rectangle" "1526.415,1801" "1549.9433,1825.9185")
(command "_array" "last" "" "R" "135" "3" "25.9185" "24.5283")
(command "_rectangle" "1601,1801" "1624.5283,1825.9185")
(command "_array" "last" "" "R" "135" "3" "25.9185" "24.5283")
(command "_layer" "set" "vgrooveFDA" "")
(command "_rectangle" "1674.585,-2233" "1525.415,-1933")
(command "_layer" "set" "nitride" "")
(command "_layer" "set" "holes" "")
(command "_circle" "1677.085,331.5" "0.5")
(command "_array" "last" "" "R" "379" "1" "3" "2.5")
(command "_circle" "1522.915,331.5" "0.5")
(command "_array" "last" "" "R" "379" "1" "3" "-2.5")
(command "_layer" "set" "nitride" "")
(command "_layer" "set" "window" "")
(command "_layer" "set" "window" "")
(command "_rectangle" "1679.585,0" "1840.415,1800")
(command "._fillet" "radius" "20" "._fillet" "P" (entlast))
(command "_layer" "set" "grid" "")
(command "_rectangle" "1680.585,1" "1702.4179,25.7")
(command "_array" "last" "" "R" "70" "7" "25.7" "22.8329")
(command "_layer" "set" "nitride" "")
; DRAWING REGION LAYER
(command "_layer" "set" "regionLayer5" "")
(command "_rectangle" "1520,-460" "1680,2260")
(command "_layer" "set" "nitride" "")
(setq coupler5 nil)
(setq singlenanobeam5 nil)
(setq anglednodearray5 nil)
(setq cooledsinglenanobeam5 nil)
(setq yjunction5 nil)
; DEVICE #6
(command "_layer" "set" "window" "")
(command "_circle" "1832.915,-415" "5")
(command "_circle" "1832.915,-402.5" "5")
(command "_circle" "1832.915,-390" "5")
(command "_circle" "1832.915,-377.5" "5")
(command "_circle" "1820.415,-415" "5")
(command "_circle" "1820.415,-402.5" "5")
(command "_layer" "set" "nitride" "")
(setq currobj nil)
(setq currobj (ssadd))
; DRAWING COUPLER
(setq coords (list 
(list 1920.0595 -415) 
(list 1920.0595 -413) 
(list 1993.585 -413) 
(list 1993.585 -413) 
(list 1993.9677 -413.0761) 
(list 1994.2921 -413.2929) 
(list 1994.5089 -413.6173) 
(list 1994.585 -414) 
(list 1994.585 -411.8) 
(list 1994.585 -411.8) 
(list 1994.5089 -412.1827) 
(list 1994.2921 -412.5071) 
(list 1993.9677 -412.7239) 
(list 1993.585 -412.8) 
(list 1920.0595 -412.8) 
(list 1920.0595 -410.8) 
(list 1919.9405 -410.8) 
(list 1919.9405 -412.8) 
(list 1846.415 -412.8) 
(list 1846.0323 -412.7239) 
(list 1845.7079 -412.5071) 
(list 1845.4911 -412.1827) 
(list 1845.415 -411.8) 
(list 1845.415 -411.8) 
(list 1845.415 -414) 
(list 1845.4911 -413.6173) 
(list 1845.7079 -413.2929) 
(list 1846.0323 -413.0761) 
(list 1846.415 -413) 
(list 1846.415 -413) 
(list 1919.9405 -413) 
(list 1919.9405 -415)))
(apply 'command (append '("pline") coords '("c")))
(setq currobj (ssadd (entlast) currobj))
(command "._fillet" "radius" "0.3" "._fillet" "P" (entlast))
(command "_layer" "set" "holes" "")
(command "_circle" "1920,-412.9" "0.113")
(setq currobj (ssadd (entlast) currobj))
(command "_layer" "set" "nitride" "")
(command "_layer" "set" "text" "")
(command "_circle" "1919.2,-415" "0.075")
(command "_circle" "1919.2,-414.7" "0.075")
(command "_circle" "1919.2,-414.4" "0.075")
(command "_circle" "1918.9,-415" "0.075")
(command "_circle" "1918.9,-414.7" "0.075")
(command "_circle" "1918.9,-414.4" "0.075")
(command "_circle" "1918.6,-415" "0.075")
(command "_circle" "1918.6,-414.7" "0.075")
(command "_circle" "1918.6,-414.4" "0.075")
(command "_layer" "set" "nitride" "")
(command "_layer" "set" "prebias" "")
(command "_rectangle" "1845.415,-414" "1994.585,-411.8")
(setq currobj (ssadd (entlast) currobj))
(command "_rectangle" "1919.9405,-415" "1920.0595,-410.8")
(setq currobj (ssadd (entlast) currobj))
(command "_layer" "set" "nitride" "")
(setq coupler6 currobj)
(setq currobj nil)
(setq currobj (ssadd))
; DRAWING SINGLE NANOBEAM
(setq coords (list 
(list 1920.0595 -410.8) 
(list 1920.0595 -409.1417) 
(list 1920.0595 -407.4833) 
(list 1920.0595 -405.825) 
(list 1920.0595 -404.1667) 
(list 1920.0595 -402.5083) 
(list 1920.0595 -400.85) 
(list 1920.0595 -399.1917) 
(list 1920.0595 -397.5333) 
(list 1920.0596 -395.875) 
(list 1920.0596 -394.2167) 
(list 1920.0596 -392.5583) 
(list 1920.0596 -390.9) 
(list 1920.0597 -389.2417) 
(list 1920.0597 -387.5833) 
(list 1920.0597 -385.925) 
(list 1920.0598 -384.2667) 
(list 1920.0599 -382.6083) 
(list 1920.0599 -380.95) 
(list 1920.06 -379.2917) 
(list 1920.0601 -377.6333) 
(list 1920.0602 -375.975) 
(list 1920.0603 -374.3167) 
(list 1920.0604 -372.6583) 
(list 1920.0605 -371) 
(list 1920.0606 -369.3417) 
(list 1920.0608 -367.6833) 
(list 1920.0609 -366.025) 
(list 1920.0611 -364.3667) 
(list 1920.0613 -362.7083) 
(list 1920.0615 -361.05) 
(list 1920.0617 -359.3917) 
(list 1920.0619 -357.7333) 
(list 1920.0621 -356.075) 
(list 1920.0624 -354.4167) 
(list 1920.0626 -352.7583) 
(list 1920.0629 -351.1) 
(list 1920.0632 -349.4417) 
(list 1920.0635 -347.7833) 
(list 1920.0638 -346.125) 
(list 1920.0641 -344.4667) 
(list 1920.0645 -342.8083) 
(list 1920.0649 -341.15) 
(list 1920.0653 -339.4917) 
(list 1920.0657 -337.8333) 
(list 1920.0661 -336.175) 
(list 1920.0666 -334.5167) 
(list 1920.067 -332.8583) 
(list 1920.0675 -331.2) 
(list 1920.068 -329.5417) 
(list 1920.0686 -327.8833) 
(list 1920.0691 -326.225) 
(list 1920.0697 -324.5667) 
(list 1920.0703 -322.9083) 
(list 1920.0709 -321.25) 
(list 1920.0716 -319.5917) 
(list 1920.0723 -317.9333) 
(list 1920.0729 -316.275) 
(list 1920.0737 -314.6167) 
(list 1920.0744 -312.9583) 
(list 1920.0752 -311.3) 
(list 1920.076 -309.6417) 
(list 1920.0768 -307.9833) 
(list 1920.0777 -306.325) 
(list 1920.0785 -304.6667) 
(list 1920.0794 -303.0083) 
(list 1920.0804 -301.35) 
(list 1920.0813 -299.6917) 
(list 1920.0823 -298.0333) 
(list 1920.0834 -296.375) 
(list 1920.0844 -294.7167) 
(list 1920.0855 -293.0583) 
(list 1920.0866 -291.4) 
(list 1920.0878 -289.7417) 
(list 1920.0889 -288.0833) 
(list 1920.0901 -286.425) 
(list 1920.0914 -284.7667) 
(list 1920.0927 -283.1083) 
(list 1920.094 -281.45) 
(list 1920.0953 -279.7917) 
(list 1920.0967 -278.1333) 
(list 1920.0981 -276.475) 
(list 1920.0995 -274.8167) 
(list 1920.101 -273.1583) 
(list 1920.1025 -271.5) 
(list 1920.1041 -269.8417) 
(list 1920.1057 -268.1833) 
(list 1920.1073 -266.525) 
(list 1920.109 -264.8667) 
(list 1920.1107 -263.2083) 
(list 1920.1124 -261.55) 
(list 1920.1142 -259.8917) 
(list 1920.1161 -258.2333) 
(list 1920.1179 -256.575) 
(list 1920.1198 -254.9167) 
(list 1920.1218 -253.2583) 
(list 1920.1238 -251.6) 
(list 1920.1258 -249.9417) 
(list 1920.1279 -248.2833) 
(list 1920.13 -246.625) 
(list 1920.1321 -244.9667) 
(list 1920.1343 -243.3083) 
(list 1920.1366 -241.65) 
(list 1920.1389 -239.9917) 
(list 1920.1412 -238.3333) 
(list 1920.1436 -236.675) 
(list 1920.146 -235.0167) 
(list 1920.1485 -233.3583) 
(list 1920.151 -231.7) 
(list 1920.1536 -230.0417) 
(list 1920.1562 -228.3833) 
(list 1920.1588 -226.725) 
(list 1920.1615 -225.0667) 
(list 1920.1643 -223.4083) 
(list 1920.1671 -221.75) 
(list 1920.17 -220.0917) 
(list 1920.1729 -218.4333) 
(list 1920.1758 -216.775) 
(list 1920.1788 -215.1167) 
(list 1920.1819 -213.4583) 
(list 1920.185 -211.8) 
(list 1919.815 -211.8) 
(list 1919.8181 -213.4583) 
(list 1919.8212 -215.1167) 
(list 1919.8242 -216.775) 
(list 1919.8271 -218.4333) 
(list 1919.83 -220.0917) 
(list 1919.8329 -221.75) 
(list 1919.8357 -223.4083) 
(list 1919.8385 -225.0667) 
(list 1919.8412 -226.725) 
(list 1919.8438 -228.3833) 
(list 1919.8464 -230.0417) 
(list 1919.849 -231.7) 
(list 1919.8515 -233.3583) 
(list 1919.854 -235.0167) 
(list 1919.8564 -236.675) 
(list 1919.8588 -238.3333) 
(list 1919.8611 -239.9917) 
(list 1919.8634 -241.65) 
(list 1919.8657 -243.3083) 
(list 1919.8679 -244.9667) 
(list 1919.87 -246.625) 
(list 1919.8721 -248.2833) 
(list 1919.8742 -249.9417) 
(list 1919.8762 -251.6) 
(list 1919.8782 -253.2583) 
(list 1919.8802 -254.9167) 
(list 1919.8821 -256.575) 
(list 1919.8839 -258.2333) 
(list 1919.8858 -259.8917) 
(list 1919.8876 -261.55) 
(list 1919.8893 -263.2083) 
(list 1919.891 -264.8667) 
(list 1919.8927 -266.525) 
(list 1919.8943 -268.1833) 
(list 1919.8959 -269.8417) 
(list 1919.8975 -271.5) 
(list 1919.899 -273.1583) 
(list 1919.9005 -274.8167) 
(list 1919.9019 -276.475) 
(list 1919.9033 -278.1333) 
(list 1919.9047 -279.7917) 
(list 1919.906 -281.45) 
(list 1919.9073 -283.1083) 
(list 1919.9086 -284.7667) 
(list 1919.9099 -286.425) 
(list 1919.9111 -288.0833) 
(list 1919.9122 -289.7417) 
(list 1919.9134 -291.4) 
(list 1919.9145 -293.0583) 
(list 1919.9156 -294.7167) 
(list 1919.9166 -296.375) 
(list 1919.9177 -298.0333) 
(list 1919.9187 -299.6917) 
(list 1919.9196 -301.35) 
(list 1919.9206 -303.0083) 
(list 1919.9215 -304.6667) 
(list 1919.9223 -306.325) 
(list 1919.9232 -307.9833) 
(list 1919.924 -309.6417) 
(list 1919.9248 -311.3) 
(list 1919.9256 -312.9583) 
(list 1919.9263 -314.6167) 
(list 1919.9271 -316.275) 
(list 1919.9277 -317.9333) 
(list 1919.9284 -319.5917) 
(list 1919.9291 -321.25) 
(list 1919.9297 -322.9083) 
(list 1919.9303 -324.5667) 
(list 1919.9309 -326.225) 
(list 1919.9314 -327.8833) 
(list 1919.932 -329.5417) 
(list 1919.9325 -331.2) 
(list 1919.933 -332.8583) 
(list 1919.9334 -334.5167) 
(list 1919.9339 -336.175) 
(list 1919.9343 -337.8333) 
(list 1919.9347 -339.4917) 
(list 1919.9351 -341.15) 
(list 1919.9355 -342.8083) 
(list 1919.9359 -344.4667) 
(list 1919.9362 -346.125) 
(list 1919.9365 -347.7833) 
(list 1919.9368 -349.4417) 
(list 1919.9371 -351.1) 
(list 1919.9374 -352.7583) 
(list 1919.9376 -354.4167) 
(list 1919.9379 -356.075) 
(list 1919.9381 -357.7333) 
(list 1919.9383 -359.3917) 
(list 1919.9385 -361.05) 
(list 1919.9387 -362.7083) 
(list 1919.9389 -364.3667) 
(list 1919.9391 -366.025) 
(list 1919.9392 -367.6833) 
(list 1919.9394 -369.3417) 
(list 1919.9395 -371) 
(list 1919.9396 -372.6583) 
(list 1919.9397 -374.3167) 
(list 1919.9398 -375.975) 
(list 1919.9399 -377.6333) 
(list 1919.94 -379.2917) 
(list 1919.9401 -380.95) 
(list 1919.9401 -382.6083) 
(list 1919.9402 -384.2667) 
(list 1919.9403 -385.925) 
(list 1919.9403 -387.5833) 
(list 1919.9403 -389.2417) 
(list 1919.9404 -390.9) 
(list 1919.9404 -392.5583) 
(list 1919.9404 -394.2167) 
(list 1919.9404 -395.875) 
(list 1919.9405 -397.5333) 
(list 1919.9405 -399.1917) 
(list 1919.9405 -400.85) 
(list 1919.9405 -402.5083) 
(list 1919.9405 -404.1667) 
(list 1919.9405 -405.825) 
(list 1919.9405 -407.4833) 
(list 1919.9405 -409.1417) 
(list 1919.9405 -410.8)))
(apply 'command (append '("pline") coords '("c")))
(setq currobj (ssadd (entlast) currobj))
(command "_layer" "set" "prebias" "")
(command "_rectangle" "1919.815,-410.8" "1920.185,-211.8")
(setq currobj (ssadd (entlast) currobj))
(command "_layer" "set" "nitride" "")
(setq singlenanobeam6 currobj)
(setq currobj nil)
(setq currobj (ssadd))
; DRAWING NODE ARRAY
(setq coords (list 
(list 1920.185 -211.8) 
(list 1920.5625 -201.8) 
(list 1920.5625 -201.8) 
(list 1920.5625 -200.8) 
(list 1994.585 -212.6864) 
(list 1994.585 -207.7434) 
(list 1920.5625 -197.357) 
(list 1920.5625 -196.357) 
(list 1920.5625 -196.357) 
(list 1920.2625 -186.357) 
(list 1919.7375 -186.357) 
(list 1919.4375 -196.357) 
(list 1919.4375 -196.357) 
(list 1919.4375 -197.357) 
(list 1845.415 -207.7434) 
(list 1845.415 -212.6864) 
(list 1919.4375 -200.8) 
(list 1919.4375 -201.8) 
(list 1919.4375 -201.8) 
(list 1919.815 -211.8)))
(apply 'command (append '("pline") coords '("c")))
(setq currobj (ssadd (entlast) currobj))
(command "_layer" "set" "prebias" "")
(setq coords (list 
(list 1919.4375 -212.6864) 
(list 1919.4375 -200.8) 
(list 1845.415 -212.6864) 
(list 1845.415 -207.7434) 
(list 1919.4375 -197.357) 
(list 1919.4375 -186.357) 
(list 1920.5625 -186.357) 
(list 1920.5625 -197.357) 
(list 1994.585 -207.7434) 
(list 1994.585 -212.6864) 
(list 1920.5625 -200.8) 
(list 1920.5625 -212.6864)))
(apply 'command (append '("pline") coords '("c")))
(setq currobj (ssadd (entlast) currobj))
(command "_layer" "set" "nitride" "")
(command "_layer" "set" "fda1" "")
(setq coords (list 
(list 1920.5625 -200.657) 
(list 1994.585 -212.5434) 
(list 1994.585 -212.3664) 
(list 1920.5625 -200.58)))
(apply 'command (append '("pline") coords '("c")))
(setq currobj (ssadd (entlast) currobj))
(setq coords (list 
(list 1920.5625 -200.437) 
(list 1994.585 -212.2234) 
(list 1994.585 -212.0464) 
(list 1920.5625 -200.36)))
(apply 'command (append '("pline") coords '("c")))
(setq currobj (ssadd (entlast) currobj))
(setq coords (list 
(list 1920.5625 -200.217) 
(list 1994.585 -211.9034) 
(list 1994.585 -211.7264) 
(list 1920.5625 -200.14)))
(apply 'command (append '("pline") coords '("c")))
(setq currobj (ssadd (entlast) currobj))
(setq coords (list 
(list 1920.5625 -199.997) 
(list 1994.585 -211.5834) 
(list 1994.585 -211.4064) 
(list 1920.5625 -199.92)))
(apply 'command (append '("pline") coords '("c")))
(setq currobj (ssadd (entlast) currobj))
(setq coords (list 
(list 1920.5625 -199.777) 
(list 1994.585 -211.2634) 
(list 1994.585 -211.0864) 
(list 1920.5625 -199.7)))
(apply 'command (append '("pline") coords '("c")))
(setq currobj (ssadd (entlast) currobj))
(setq coords (list 
(list 1920.5625 -199.557) 
(list 1994.585 -210.9434) 
(list 1994.585 -210.7664) 
(list 1920.5625 -199.48)))
(apply 'command (append '("pline") coords '("c")))
(setq currobj (ssadd (entlast) currobj))
(setq coords (list 
(list 1920.5625 -199.337) 
(list 1994.585 -210.6234) 
(list 1994.585 -210.4464) 
(list 1920.5625 -199.26)))
(apply 'command (append '("pline") coords '("c")))
(setq currobj (ssadd (entlast) currobj))
(setq coords (list 
(list 1920.5625 -199.117) 
(list 1994.585 -210.3034) 
(list 1994.585 -210.1264) 
(list 1920.5625 -199.04)))
(apply 'command (append '("pline") coords '("c")))
(setq currobj (ssadd (entlast) currobj))
(setq coords (list 
(list 1920.5625 -198.897) 
(list 1994.585 -209.9834) 
(list 1994.585 -209.8064) 
(list 1920.5625 -198.82)))
(apply 'command (append '("pline") coords '("c")))
(setq currobj (ssadd (entlast) currobj))
(setq coords (list 
(list 1920.5625 -198.677) 
(list 1994.585 -209.6634) 
(list 1994.585 -209.4864) 
(list 1920.5625 -198.6)))
(apply 'command (append '("pline") coords '("c")))
(setq currobj (ssadd (entlast) currobj))
(setq coords (list 
(list 1920.5625 -198.457) 
(list 1994.585 -209.3434) 
(list 1994.585 -209.1664) 
(list 1920.5625 -198.38)))
(apply 'command (append '("pline") coords '("c")))
(setq currobj (ssadd (entlast) currobj))
(setq coords (list 
(list 1920.5625 -198.237) 
(list 1994.585 -209.0234) 
(list 1994.585 -208.8464) 
(list 1920.5625 -198.16)))
(apply 'command (append '("pline") coords '("c")))
(setq currobj (ssadd (entlast) currobj))
(setq coords (list 
(list 1920.5625 -198.017) 
(list 1994.585 -208.7034) 
(list 1994.585 -208.5264) 
(list 1920.5625 -197.94)))
(apply 'command (append '("pline") coords '("c")))
(setq currobj (ssadd (entlast) currobj))
(setq coords (list 
(list 1920.5625 -197.797) 
(list 1994.585 -208.3834) 
(list 1994.585 -208.2064) 
(list 1920.5625 -197.72)))
(apply 'command (append '("pline") coords '("c")))
(setq currobj (ssadd (entlast) currobj))
(setq coords (list 
(list 1920.5625 -197.577) 
(list 1994.585 -208.0634) 
(list 1994.585 -207.8864) 
(list 1920.5625 -197.5)))
(apply 'command (append '("pline") coords '("c")))
(setq currobj (ssadd (entlast) currobj))
(setq coords (list 
(list 1919.4375 -197.5) 
(list 1845.415 -207.8864) 
(list 1845.415 -208.0634) 
(list 1919.4375 -197.577)))
(apply 'command (append '("pline") coords '("c")))
(setq currobj (ssadd (entlast) currobj))
(setq coords (list 
(list 1919.4375 -197.72) 
(list 1845.415 -208.2064) 
(list 1845.415 -208.3834) 
(list 1919.4375 -197.797)))
(apply 'command (append '("pline") coords '("c")))
(setq currobj (ssadd (entlast) currobj))
(setq coords (list 
(list 1919.4375 -197.94) 
(list 1845.415 -208.5264) 
(list 1845.415 -208.7034) 
(list 1919.4375 -198.017)))
(apply 'command (append '("pline") coords '("c")))
(setq currobj (ssadd (entlast) currobj))
(setq coords (list 
(list 1919.4375 -198.16) 
(list 1845.415 -208.8464) 
(list 1845.415 -209.0234) 
(list 1919.4375 -198.237)))
(apply 'command (append '("pline") coords '("c")))
(setq currobj (ssadd (entlast) currobj))
(setq coords (list 
(list 1919.4375 -198.38) 
(list 1845.415 -209.1664) 
(list 1845.415 -209.3434) 
(list 1919.4375 -198.457)))
(apply 'command (append '("pline") coords '("c")))
(setq currobj (ssadd (entlast) currobj))
(setq coords (list 
(list 1919.4375 -198.6) 
(list 1845.415 -209.4864) 
(list 1845.415 -209.6634) 
(list 1919.4375 -198.677)))
(apply 'command (append '("pline") coords '("c")))
(setq currobj (ssadd (entlast) currobj))
(setq coords (list 
(list 1919.4375 -198.82) 
(list 1845.415 -209.8064) 
(list 1845.415 -209.9834) 
(list 1919.4375 -198.897)))
(apply 'command (append '("pline") coords '("c")))
(setq currobj (ssadd (entlast) currobj))
(setq coords (list 
(list 1919.4375 -199.04) 
(list 1845.415 -210.1264) 
(list 1845.415 -210.3034) 
(list 1919.4375 -199.117)))
(apply 'command (append '("pline") coords '("c")))
(setq currobj (ssadd (entlast) currobj))
(setq coords (list 
(list 1919.4375 -199.26) 
(list 1845.415 -210.4464) 
(list 1845.415 -210.6234) 
(list 1919.4375 -199.337)))
(apply 'command (append '("pline") coords '("c")))
(setq currobj (ssadd (entlast) currobj))
(setq coords (list 
(list 1919.4375 -199.48) 
(list 1845.415 -210.7664) 
(list 1845.415 -210.9434) 
(list 1919.4375 -199.557)))
(apply 'command (append '("pline") coords '("c")))
(setq currobj (ssadd (entlast) currobj))
(setq coords (list 
(list 1919.4375 -199.7) 
(list 1845.415 -211.0864) 
(list 1845.415 -211.2634) 
(list 1919.4375 -199.777)))
(apply 'command (append '("pline") coords '("c")))
(setq currobj (ssadd (entlast) currobj))
(setq coords (list 
(list 1919.4375 -199.92) 
(list 1845.415 -211.4064) 
(list 1845.415 -211.5834) 
(list 1919.4375 -199.997)))
(apply 'command (append '("pline") coords '("c")))
(setq currobj (ssadd (entlast) currobj))
(setq coords (list 
(list 1919.4375 -200.14) 
(list 1845.415 -211.7264) 
(list 1845.415 -211.9034) 
(list 1919.4375 -200.217)))
(apply 'command (append '("pline") coords '("c")))
(setq currobj (ssadd (entlast) currobj))
(setq coords (list 
(list 1919.4375 -200.36) 
(list 1845.415 -212.0464) 
(list 1845.415 -212.2234) 
(list 1919.4375 -200.437)))
(apply 'command (append '("pline") coords '("c")))
(setq currobj (ssadd (entlast) currobj))
(setq coords (list 
(list 1919.4375 -200.58) 
(list 1845.415 -212.3664) 
(list 1845.415 -212.5434) 
(list 1919.4375 -200.657)))
(apply 'command (append '("pline") coords '("c")))
(setq currobj (ssadd (entlast) currobj))
(command "_layer" "set" "nitride" "")
(command "_layer" "set" "text" "")
(command "_circle" "1918.985,-211.8" "0.075")
(command "_circle" "1918.985,-211.5" "0.075")
(command "_circle" "1918.985,-211.2" "0.075")
(command "_circle" "1918.985,-210.9" "0.075")
(command "_circle" "1918.985,-210.6" "0.075")
(command "_circle" "1918.685,-211.8" "0.075")
(command "_circle" "1918.685,-211.5" "0.075")
(command "_circle" "1918.685,-211.2" "0.075")
(command "_circle" "1918.685,-210.9" "0.075")
(command "_circle" "1918.685,-210.6" "0.075")
(command "_circle" "1918.385,-211.8" "0.075")
(command "_circle" "1918.385,-211.5" "0.075")
(command "_circle" "1918.385,-211.2" "0.075")
(command "_circle" "1918.385,-210.9" "0.075")
(command "_circle" "1918.385,-210.6" "0.075")
(command "_circle" "1918.085,-211.8" "0.075")
(command "_circle" "1918.085,-211.5" "0.075")
(command "_circle" "1918.085,-211.2" "0.075")
(command "_circle" "1918.085,-210.9" "0.075")
(command "_circle" "1918.085,-210.6" "0.075")
(command "_circle" "1917.785,-211.8" "0.075")
(command "_circle" "1917.785,-211.5" "0.075")
(command "_circle" "1917.785,-211.2" "0.075")
(command "_circle" "1917.785,-210.9" "0.075")
(command "_circle" "1917.785,-210.6" "0.075")
(command "_layer" "set" "nitride" "")
(setq anglednodearray6 currobj)
(setq currobj nil)
(setq currobj (ssadd))
; DRAWING COOLED SINGLE NANOBEAM
(setq coords (list 
(list 1920.2625 -186.357) 
(list 1920.2625 -181.357) 
(list 1919.7375 -181.357) 
(list 1919.7375 -186.357)))
(apply 'command (append '("pline") coords '("c")))
(setq currobj (ssadd (entlast) currobj))
(command "_layer" "set" "prebias" "")
(command "_rectangle" "1919.7375,-186.357" "1920.2625,-181.357")
(setq currobj (ssadd (entlast) currobj))
(command "_layer" "set" "nitride" "")
(setq coords (list 
(list 1920.2625 -181.357) 
(list 1920.5625 -171.357) 
(list 1920.5625 -171.357) 
(list 1920.5625 -170.357) 
(list 1994.585 -171.107) 
(list 1994.585 -166.164) 
(list 1920.5625 -166.914) 
(list 1920.5625 -165.914) 
(list 1920.5625 -165.914) 
(list 1920.2625 -155.914) 
(list 1919.7375 -155.914) 
(list 1919.4375 -165.914) 
(list 1919.4375 -165.914) 
(list 1919.4375 -166.914) 
(list 1845.415 -166.164) 
(list 1845.415 -171.107) 
(list 1919.4375 -170.357) 
(list 1919.4375 -171.357) 
(list 1919.4375 -171.357) 
(list 1919.7375 -181.357)))
(apply 'command (append '("pline") coords '("c")))
(setq currobj (ssadd (entlast) currobj))
(command "_layer" "set" "prebias" "")
(setq coords (list 
(list 1919.4375 -181.357) 
(list 1919.4375 -170.357) 
(list 1845.415 -171.107) 
(list 1845.415 -166.164) 
(list 1919.4375 -166.914) 
(list 1919.4375 -155.914) 
(list 1920.5625 -155.914) 
(list 1920.5625 -166.914) 
(list 1994.585 -166.164) 
(list 1994.585 -171.107) 
(list 1920.5625 -170.357) 
(list 1920.5625 -181.357)))
(apply 'command (append '("pline") coords '("c")))
(setq currobj (ssadd (entlast) currobj))
(command "_layer" "set" "nitride" "")
(command "_layer" "set" "fda1" "")
(setq coords (list 
(list 1920.5625 -170.214) 
(list 1994.585 -170.964) 
(list 1994.585 -170.787) 
(list 1920.5625 -170.137)))
(apply 'command (append '("pline") coords '("c")))
(setq currobj (ssadd (entlast) currobj))
(setq coords (list 
(list 1920.5625 -169.994) 
(list 1994.585 -170.644) 
(list 1994.585 -170.467) 
(list 1920.5625 -169.917)))
(apply 'command (append '("pline") coords '("c")))
(setq currobj (ssadd (entlast) currobj))
(setq coords (list 
(list 1920.5625 -169.774) 
(list 1994.585 -170.324) 
(list 1994.585 -170.147) 
(list 1920.5625 -169.697)))
(apply 'command (append '("pline") coords '("c")))
(setq currobj (ssadd (entlast) currobj))
(setq coords (list 
(list 1920.5625 -169.554) 
(list 1994.585 -170.004) 
(list 1994.585 -169.827) 
(list 1920.5625 -169.477)))
(apply 'command (append '("pline") coords '("c")))
(setq currobj (ssadd (entlast) currobj))
(setq coords (list 
(list 1920.5625 -169.334) 
(list 1994.585 -169.684) 
(list 1994.585 -169.507) 
(list 1920.5625 -169.257)))
(apply 'command (append '("pline") coords '("c")))
(setq currobj (ssadd (entlast) currobj))
(setq coords (list 
(list 1920.5625 -169.114) 
(list 1994.585 -169.364) 
(list 1994.585 -169.187) 
(list 1920.5625 -169.037)))
(apply 'command (append '("pline") coords '("c")))
(setq currobj (ssadd (entlast) currobj))
(setq coords (list 
(list 1920.5625 -168.894) 
(list 1994.585 -169.044) 
(list 1994.585 -168.867) 
(list 1920.5625 -168.817)))
(apply 'command (append '("pline") coords '("c")))
(setq currobj (ssadd (entlast) currobj))
(setq coords (list 
(list 1920.5625 -168.674) 
(list 1994.585 -168.724) 
(list 1994.585 -168.547) 
(list 1920.5625 -168.597)))
(apply 'command (append '("pline") coords '("c")))
(setq currobj (ssadd (entlast) currobj))
(setq coords (list 
(list 1920.5625 -168.454) 
(list 1994.585 -168.404) 
(list 1994.585 -168.227) 
(list 1920.5625 -168.377)))
(apply 'command (append '("pline") coords '("c")))
(setq currobj (ssadd (entlast) currobj))
(setq coords (list 
(list 1920.5625 -168.234) 
(list 1994.585 -168.084) 
(list 1994.585 -167.907) 
(list 1920.5625 -168.157)))
(apply 'command (append '("pline") coords '("c")))
(setq currobj (ssadd (entlast) currobj))
(setq coords (list 
(list 1920.5625 -168.014) 
(list 1994.585 -167.764) 
(list 1994.585 -167.587) 
(list 1920.5625 -167.937)))
(apply 'command (append '("pline") coords '("c")))
(setq currobj (ssadd (entlast) currobj))
(setq coords (list 
(list 1920.5625 -167.794) 
(list 1994.585 -167.444) 
(list 1994.585 -167.267) 
(list 1920.5625 -167.717)))
(apply 'command (append '("pline") coords '("c")))
(setq currobj (ssadd (entlast) currobj))
(setq coords (list 
(list 1920.5625 -167.574) 
(list 1994.585 -167.124) 
(list 1994.585 -166.947) 
(list 1920.5625 -167.497)))
(apply 'command (append '("pline") coords '("c")))
(setq currobj (ssadd (entlast) currobj))
(setq coords (list 
(list 1920.5625 -167.354) 
(list 1994.585 -166.804) 
(list 1994.585 -166.627) 
(list 1920.5625 -167.277)))
(apply 'command (append '("pline") coords '("c")))
(setq currobj (ssadd (entlast) currobj))
(setq coords (list 
(list 1920.5625 -167.134) 
(list 1994.585 -166.484) 
(list 1994.585 -166.307) 
(list 1920.5625 -167.057)))
(apply 'command (append '("pline") coords '("c")))
(setq currobj (ssadd (entlast) currobj))
(setq coords (list 
(list 1919.4375 -167.057) 
(list 1845.415 -166.307) 
(list 1845.415 -166.484) 
(list 1919.4375 -167.134)))
(apply 'command (append '("pline") coords '("c")))
(setq currobj (ssadd (entlast) currobj))
(setq coords (list 
(list 1919.4375 -167.277) 
(list 1845.415 -166.627) 
(list 1845.415 -166.804) 
(list 1919.4375 -167.354)))
(apply 'command (append '("pline") coords '("c")))
(setq currobj (ssadd (entlast) currobj))
(setq coords (list 
(list 1919.4375 -167.497) 
(list 1845.415 -166.947) 
(list 1845.415 -167.124) 
(list 1919.4375 -167.574)))
(apply 'command (append '("pline") coords '("c")))
(setq currobj (ssadd (entlast) currobj))
(setq coords (list 
(list 1919.4375 -167.717) 
(list 1845.415 -167.267) 
(list 1845.415 -167.444) 
(list 1919.4375 -167.794)))
(apply 'command (append '("pline") coords '("c")))
(setq currobj (ssadd (entlast) currobj))
(setq coords (list 
(list 1919.4375 -167.937) 
(list 1845.415 -167.587) 
(list 1845.415 -167.764) 
(list 1919.4375 -168.014)))
(apply 'command (append '("pline") coords '("c")))
(setq currobj (ssadd (entlast) currobj))
(setq coords (list 
(list 1919.4375 -168.157) 
(list 1845.415 -167.907) 
(list 1845.415 -168.084) 
(list 1919.4375 -168.234)))
(apply 'command (append '("pline") coords '("c")))
(setq currobj (ssadd (entlast) currobj))
(setq coords (list 
(list 1919.4375 -168.377) 
(list 1845.415 -168.227) 
(list 1845.415 -168.404) 
(list 1919.4375 -168.454)))
(apply 'command (append '("pline") coords '("c")))
(setq currobj (ssadd (entlast) currobj))
(setq coords (list 
(list 1919.4375 -168.597) 
(list 1845.415 -168.547) 
(list 1845.415 -168.724) 
(list 1919.4375 -168.674)))
(apply 'command (append '("pline") coords '("c")))
(setq currobj (ssadd (entlast) currobj))
(setq coords (list 
(list 1919.4375 -168.817) 
(list 1845.415 -168.867) 
(list 1845.415 -169.044) 
(list 1919.4375 -168.894)))
(apply 'command (append '("pline") coords '("c")))
(setq currobj (ssadd (entlast) currobj))
(setq coords (list 
(list 1919.4375 -169.037) 
(list 1845.415 -169.187) 
(list 1845.415 -169.364) 
(list 1919.4375 -169.114)))
(apply 'command (append '("pline") coords '("c")))
(setq currobj (ssadd (entlast) currobj))
(setq coords (list 
(list 1919.4375 -169.257) 
(list 1845.415 -169.507) 
(list 1845.415 -169.684) 
(list 1919.4375 -169.334)))
(apply 'command (append '("pline") coords '("c")))
(setq currobj (ssadd (entlast) currobj))
(setq coords (list 
(list 1919.4375 -169.477) 
(list 1845.415 -169.827) 
(list 1845.415 -170.004) 
(list 1919.4375 -169.554)))
(apply 'command (append '("pline") coords '("c")))
(setq currobj (ssadd (entlast) currobj))
(setq coords (list 
(list 1919.4375 -169.697) 
(list 1845.415 -170.147) 
(list 1845.415 -170.324) 
(list 1919.4375 -169.774)))
(apply 'command (append '("pline") coords '("c")))
(setq currobj (ssadd (entlast) currobj))
(setq coords (list 
(list 1919.4375 -169.917) 
(list 1845.415 -170.467) 
(list 1845.415 -170.644) 
(list 1919.4375 -169.994)))
(apply 'command (append '("pline") coords '("c")))
(setq currobj (ssadd (entlast) currobj))
(setq coords (list 
(list 1919.4375 -170.137) 
(list 1845.415 -170.787) 
(list 1845.415 -170.964) 
(list 1919.4375 -170.214)))
(apply 'command (append '("pline") coords '("c")))
(setq currobj (ssadd (entlast) currobj))
(command "_layer" "set" "nitride" "")
(command "_layer" "set" "text" "")
(command "_circle" "1919.0625,-181.357" "0.075")
(command "_circle" "1919.0625,-181.057" "0.075")
(command "_circle" "1919.0625,-180.757" "0.075")
(command "_circle" "1919.0625,-180.457" "0.075")
(command "_circle" "1919.0625,-180.157" "0.075")
(command "_circle" "1918.7625,-181.357" "0.075")
(command "_circle" "1918.7625,-181.057" "0.075")
(command "_circle" "1918.7625,-180.757" "0.075")
(command "_circle" "1918.7625,-180.457" "0.075")
(command "_circle" "1918.7625,-180.157" "0.075")
(command "_circle" "1918.4625,-181.357" "0.075")
(command "_circle" "1918.4625,-181.057" "0.075")
(command "_circle" "1918.4625,-180.757" "0.075")
(command "_circle" "1918.4625,-180.457" "0.075")
(command "_circle" "1918.4625,-180.157" "0.075")
(command "_circle" "1918.1625,-181.357" "0.075")
(command "_circle" "1918.1625,-181.057" "0.075")
(command "_circle" "1918.1625,-180.757" "0.075")
(command "_circle" "1918.1625,-180.457" "0.075")
(command "_circle" "1918.1625,-180.157" "0.075")
(command "_circle" "1917.8625,-181.357" "0.075")
(command "_circle" "1917.8625,-181.057" "0.075")
(command "_circle" "1917.8625,-180.757" "0.075")
(command "_circle" "1917.8625,-180.457" "0.075")
(command "_circle" "1917.8625,-180.157" "0.075")
(command "_layer" "set" "nitride" "")
(setq coords (list 
(list 1920.2625 -155.914) 
(list 1920.2625 -40.2693) 
(list 1919.7375 -40.2693) 
(list 1919.7375 -155.914)))
(apply 'command (append '("pline") coords '("c")))
(setq currobj (ssadd (entlast) currobj))
(command "_layer" "set" "prebias" "")
(command "_rectangle" "1919.7375,-155.914" "1920.2625,-40.2693")
(setq currobj (ssadd (entlast) currobj))
(command "_layer" "set" "nitride" "")
(setq coords (list 
(list 1920.2625 -40.2693) 
(list 1920.5625 -30.2693) 
(list 1920.5625 -30.2693) 
(list 1920.5625 -29.2693) 
(list 1994.585 -30.0193) 
(list 1994.585 -25.0763) 
(list 1920.5625 -25.8263) 
(list 1920.5625 -24.8263) 
(list 1920.5625 -24.8263) 
(list 1920.2625 -14.8263) 
(list 1919.7375 -14.8263) 
(list 1919.4375 -24.8263) 
(list 1919.4375 -24.8263) 
(list 1919.4375 -25.8263) 
(list 1845.415 -25.0763) 
(list 1845.415 -30.0193) 
(list 1919.4375 -29.2693) 
(list 1919.4375 -30.2693) 
(list 1919.4375 -30.2693) 
(list 1919.7375 -40.2693)))
(apply 'command (append '("pline") coords '("c")))
(setq currobj (ssadd (entlast) currobj))
(command "_layer" "set" "prebias" "")
(setq coords (list 
(list 1919.4375 -40.2693) 
(list 1919.4375 -29.2693) 
(list 1845.415 -30.0193) 
(list 1845.415 -25.0763) 
(list 1919.4375 -25.8263) 
(list 1919.4375 -14.8263) 
(list 1920.5625 -14.8263) 
(list 1920.5625 -25.8263) 
(list 1994.585 -25.0763) 
(list 1994.585 -30.0193) 
(list 1920.5625 -29.2693) 
(list 1920.5625 -40.2693)))
(apply 'command (append '("pline") coords '("c")))
(setq currobj (ssadd (entlast) currobj))
(command "_layer" "set" "nitride" "")
(command "_layer" "set" "fda1" "")
(setq coords (list 
(list 1920.5625 -29.1263) 
(list 1994.585 -29.8763) 
(list 1994.585 -29.6993) 
(list 1920.5625 -29.0493)))
(apply 'command (append '("pline") coords '("c")))
(setq currobj (ssadd (entlast) currobj))
(setq coords (list 
(list 1920.5625 -28.9063) 
(list 1994.585 -29.5563) 
(list 1994.585 -29.3793) 
(list 1920.5625 -28.8293)))
(apply 'command (append '("pline") coords '("c")))
(setq currobj (ssadd (entlast) currobj))
(setq coords (list 
(list 1920.5625 -28.6863) 
(list 1994.585 -29.2363) 
(list 1994.585 -29.0593) 
(list 1920.5625 -28.6093)))
(apply 'command (append '("pline") coords '("c")))
(setq currobj (ssadd (entlast) currobj))
(setq coords (list 
(list 1920.5625 -28.4663) 
(list 1994.585 -28.9163) 
(list 1994.585 -28.7393) 
(list 1920.5625 -28.3893)))
(apply 'command (append '("pline") coords '("c")))
(setq currobj (ssadd (entlast) currobj))
(setq coords (list 
(list 1920.5625 -28.2463) 
(list 1994.585 -28.5963) 
(list 1994.585 -28.4193) 
(list 1920.5625 -28.1693)))
(apply 'command (append '("pline") coords '("c")))
(setq currobj (ssadd (entlast) currobj))
(setq coords (list 
(list 1920.5625 -28.0263) 
(list 1994.585 -28.2763) 
(list 1994.585 -28.0993) 
(list 1920.5625 -27.9493)))
(apply 'command (append '("pline") coords '("c")))
(setq currobj (ssadd (entlast) currobj))
(setq coords (list 
(list 1920.5625 -27.8063) 
(list 1994.585 -27.9563) 
(list 1994.585 -27.7793) 
(list 1920.5625 -27.7293)))
(apply 'command (append '("pline") coords '("c")))
(setq currobj (ssadd (entlast) currobj))
(setq coords (list 
(list 1920.5625 -27.5863) 
(list 1994.585 -27.6363) 
(list 1994.585 -27.4593) 
(list 1920.5625 -27.5093)))
(apply 'command (append '("pline") coords '("c")))
(setq currobj (ssadd (entlast) currobj))
(setq coords (list 
(list 1920.5625 -27.3663) 
(list 1994.585 -27.3163) 
(list 1994.585 -27.1393) 
(list 1920.5625 -27.2893)))
(apply 'command (append '("pline") coords '("c")))
(setq currobj (ssadd (entlast) currobj))
(setq coords (list 
(list 1920.5625 -27.1463) 
(list 1994.585 -26.9963) 
(list 1994.585 -26.8193) 
(list 1920.5625 -27.0693)))
(apply 'command (append '("pline") coords '("c")))
(setq currobj (ssadd (entlast) currobj))
(setq coords (list 
(list 1920.5625 -26.9263) 
(list 1994.585 -26.6763) 
(list 1994.585 -26.4993) 
(list 1920.5625 -26.8493)))
(apply 'command (append '("pline") coords '("c")))
(setq currobj (ssadd (entlast) currobj))
(setq coords (list 
(list 1920.5625 -26.7063) 
(list 1994.585 -26.3563) 
(list 1994.585 -26.1793) 
(list 1920.5625 -26.6293)))
(apply 'command (append '("pline") coords '("c")))
(setq currobj (ssadd (entlast) currobj))
(setq coords (list 
(list 1920.5625 -26.4863) 
(list 1994.585 -26.0363) 
(list 1994.585 -25.8593) 
(list 1920.5625 -26.4093)))
(apply 'command (append '("pline") coords '("c")))
(setq currobj (ssadd (entlast) currobj))
(setq coords (list 
(list 1920.5625 -26.2663) 
(list 1994.585 -25.7163) 
(list 1994.585 -25.5393) 
(list 1920.5625 -26.1893)))
(apply 'command (append '("pline") coords '("c")))
(setq currobj (ssadd (entlast) currobj))
(setq coords (list 
(list 1920.5625 -26.0463) 
(list 1994.585 -25.3963) 
(list 1994.585 -25.2193) 
(list 1920.5625 -25.9693)))
(apply 'command (append '("pline") coords '("c")))
(setq currobj (ssadd (entlast) currobj))
(setq coords (list 
(list 1919.4375 -25.9693) 
(list 1845.415 -25.2193) 
(list 1845.415 -25.3963) 
(list 1919.4375 -26.0463)))
(apply 'command (append '("pline") coords '("c")))
(setq currobj (ssadd (entlast) currobj))
(setq coords (list 
(list 1919.4375 -26.1893) 
(list 1845.415 -25.5393) 
(list 1845.415 -25.7163) 
(list 1919.4375 -26.2663)))
(apply 'command (append '("pline") coords '("c")))
(setq currobj (ssadd (entlast) currobj))
(setq coords (list 
(list 1919.4375 -26.4093) 
(list 1845.415 -25.8593) 
(list 1845.415 -26.0363) 
(list 1919.4375 -26.4863)))
(apply 'command (append '("pline") coords '("c")))
(setq currobj (ssadd (entlast) currobj))
(setq coords (list 
(list 1919.4375 -26.6293) 
(list 1845.415 -26.1793) 
(list 1845.415 -26.3563) 
(list 1919.4375 -26.7063)))
(apply 'command (append '("pline") coords '("c")))
(setq currobj (ssadd (entlast) currobj))
(setq coords (list 
(list 1919.4375 -26.8493) 
(list 1845.415 -26.4993) 
(list 1845.415 -26.6763) 
(list 1919.4375 -26.9263)))
(apply 'command (append '("pline") coords '("c")))
(setq currobj (ssadd (entlast) currobj))
(setq coords (list 
(list 1919.4375 -27.0693) 
(list 1845.415 -26.8193) 
(list 1845.415 -26.9963) 
(list 1919.4375 -27.1463)))
(apply 'command (append '("pline") coords '("c")))
(setq currobj (ssadd (entlast) currobj))
(setq coords (list 
(list 1919.4375 -27.2893) 
(list 1845.415 -27.1393) 
(list 1845.415 -27.3163) 
(list 1919.4375 -27.3663)))
(apply 'command (append '("pline") coords '("c")))
(setq currobj (ssadd (entlast) currobj))
(setq coords (list 
(list 1919.4375 -27.5093) 
(list 1845.415 -27.4593) 
(list 1845.415 -27.6363) 
(list 1919.4375 -27.5863)))
(apply 'command (append '("pline") coords '("c")))
(setq currobj (ssadd (entlast) currobj))
(setq coords (list 
(list 1919.4375 -27.7293) 
(list 1845.415 -27.7793) 
(list 1845.415 -27.9563) 
(list 1919.4375 -27.8063)))
(apply 'command (append '("pline") coords '("c")))
(setq currobj (ssadd (entlast) currobj))
(setq coords (list 
(list 1919.4375 -27.9493) 
(list 1845.415 -28.0993) 
(list 1845.415 -28.2763) 
(list 1919.4375 -28.0263)))
(apply 'command (append '("pline") coords '("c")))
(setq currobj (ssadd (entlast) currobj))
(setq coords (list 
(list 1919.4375 -28.1693) 
(list 1845.415 -28.4193) 
(list 1845.415 -28.5963) 
(list 1919.4375 -28.2463)))
(apply 'command (append '("pline") coords '("c")))
(setq currobj (ssadd (entlast) currobj))
(setq coords (list 
(list 1919.4375 -28.3893) 
(list 1845.415 -28.7393) 
(list 1845.415 -28.9163) 
(list 1919.4375 -28.4663)))
(apply 'command (append '("pline") coords '("c")))
(setq currobj (ssadd (entlast) currobj))
(setq coords (list 
(list 1919.4375 -28.6093) 
(list 1845.415 -29.0593) 
(list 1845.415 -29.2363) 
(list 1919.4375 -28.6863)))
(apply 'command (append '("pline") coords '("c")))
(setq currobj (ssadd (entlast) currobj))
(setq coords (list 
(list 1919.4375 -28.8293) 
(list 1845.415 -29.3793) 
(list 1845.415 -29.5563) 
(list 1919.4375 -28.9063)))
(apply 'command (append '("pline") coords '("c")))
(setq currobj (ssadd (entlast) currobj))
(setq coords (list 
(list 1919.4375 -29.0493) 
(list 1845.415 -29.6993) 
(list 1845.415 -29.8763) 
(list 1919.4375 -29.1263)))
(apply 'command (append '("pline") coords '("c")))
(setq currobj (ssadd (entlast) currobj))
(command "_layer" "set" "nitride" "")
(command "_layer" "set" "text" "")
(command "_circle" "1919.0625,-40.2693" "0.075")
(command "_circle" "1919.0625,-39.9693" "0.075")
(command "_circle" "1919.0625,-39.6693" "0.075")
(command "_circle" "1919.0625,-39.3693" "0.075")
(command "_circle" "1919.0625,-39.0693" "0.075")
(command "_circle" "1918.7625,-40.2693" "0.075")
(command "_circle" "1918.7625,-39.9693" "0.075")
(command "_circle" "1918.7625,-39.6693" "0.075")
(command "_circle" "1918.7625,-39.3693" "0.075")
(command "_circle" "1918.7625,-39.0693" "0.075")
(command "_circle" "1918.4625,-40.2693" "0.075")
(command "_circle" "1918.4625,-39.9693" "0.075")
(command "_circle" "1918.4625,-39.6693" "0.075")
(command "_circle" "1918.4625,-39.3693" "0.075")
(command "_circle" "1918.4625,-39.0693" "0.075")
(command "_circle" "1918.1625,-40.2693" "0.075")
(command "_circle" "1918.1625,-39.9693" "0.075")
(command "_circle" "1918.1625,-39.6693" "0.075")
(command "_circle" "1918.1625,-39.3693" "0.075")
(command "_circle" "1918.1625,-39.0693" "0.075")
(command "_circle" "1917.8625,-40.2693" "0.075")
(command "_circle" "1917.8625,-39.9693" "0.075")
(command "_circle" "1917.8625,-39.6693" "0.075")
(command "_circle" "1917.8625,-39.3693" "0.075")
(command "_circle" "1917.8625,-39.0693" "0.075")
(command "_layer" "set" "nitride" "")
(setq coords (list 
(list 1920.2625 -14.8263) 
(list 1920.2625 100.8184) 
(list 1919.7375 100.8184) 
(list 1919.7375 -14.8263)))
(apply 'command (append '("pline") coords '("c")))
(setq currobj (ssadd (entlast) currobj))
(command "_layer" "set" "prebias" "")
(command "_rectangle" "1919.7375,-14.8263" "1920.2625,100.8184")
(setq currobj (ssadd (entlast) currobj))
(command "_layer" "set" "nitride" "")
(setq coords (list 
(list 1920.2625 100.8184) 
(list 1920.5625 110.8184) 
(list 1920.5625 110.8184) 
(list 1920.5625 111.8184) 
(list 1994.585 111.0684) 
(list 1994.585 116.0114) 
(list 1920.5625 115.2614) 
(list 1920.5625 116.2614) 
(list 1920.5625 116.2614) 
(list 1920.2625 126.2614) 
(list 1919.7375 126.2614) 
(list 1919.4375 116.2614) 
(list 1919.4375 116.2614) 
(list 1919.4375 115.2614) 
(list 1845.415 116.0114) 
(list 1845.415 111.0684) 
(list 1919.4375 111.8184) 
(list 1919.4375 110.8184) 
(list 1919.4375 110.8184) 
(list 1919.7375 100.8184)))
(apply 'command (append '("pline") coords '("c")))
(setq currobj (ssadd (entlast) currobj))
(command "_layer" "set" "prebias" "")
(setq coords (list 
(list 1919.4375 100.8184) 
(list 1919.4375 111.8184) 
(list 1845.415 111.0684) 
(list 1845.415 116.0114) 
(list 1919.4375 115.2614) 
(list 1919.4375 126.2614) 
(list 1920.5625 126.2614) 
(list 1920.5625 115.2614) 
(list 1994.585 116.0114) 
(list 1994.585 111.0684) 
(list 1920.5625 111.8184) 
(list 1920.5625 100.8184)))
(apply 'command (append '("pline") coords '("c")))
(setq currobj (ssadd (entlast) currobj))
(command "_layer" "set" "nitride" "")
(command "_layer" "set" "fda1" "")
(setq coords (list 
(list 1920.5625 111.9614) 
(list 1994.585 111.2114) 
(list 1994.585 111.3884) 
(list 1920.5625 112.0384)))
(apply 'command (append '("pline") coords '("c")))
(setq currobj (ssadd (entlast) currobj))
(setq coords (list 
(list 1920.5625 112.1814) 
(list 1994.585 111.5314) 
(list 1994.585 111.7084) 
(list 1920.5625 112.2584)))
(apply 'command (append '("pline") coords '("c")))
(setq currobj (ssadd (entlast) currobj))
(setq coords (list 
(list 1920.5625 112.4014) 
(list 1994.585 111.8514) 
(list 1994.585 112.0284) 
(list 1920.5625 112.4784)))
(apply 'command (append '("pline") coords '("c")))
(setq currobj (ssadd (entlast) currobj))
(setq coords (list 
(list 1920.5625 112.6214) 
(list 1994.585 112.1714) 
(list 1994.585 112.3484) 
(list 1920.5625 112.6984)))
(apply 'command (append '("pline") coords '("c")))
(setq currobj (ssadd (entlast) currobj))
(setq coords (list 
(list 1920.5625 112.8414) 
(list 1994.585 112.4914) 
(list 1994.585 112.6684) 
(list 1920.5625 112.9184)))
(apply 'command (append '("pline") coords '("c")))
(setq currobj (ssadd (entlast) currobj))
(setq coords (list 
(list 1920.5625 113.0614) 
(list 1994.585 112.8114) 
(list 1994.585 112.9884) 
(list 1920.5625 113.1384)))
(apply 'command (append '("pline") coords '("c")))
(setq currobj (ssadd (entlast) currobj))
(setq coords (list 
(list 1920.5625 113.2814) 
(list 1994.585 113.1314) 
(list 1994.585 113.3084) 
(list 1920.5625 113.3584)))
(apply 'command (append '("pline") coords '("c")))
(setq currobj (ssadd (entlast) currobj))
(setq coords (list 
(list 1920.5625 113.5014) 
(list 1994.585 113.4514) 
(list 1994.585 113.6284) 
(list 1920.5625 113.5784)))
(apply 'command (append '("pline") coords '("c")))
(setq currobj (ssadd (entlast) currobj))
(setq coords (list 
(list 1920.5625 113.7214) 
(list 1994.585 113.7714) 
(list 1994.585 113.9484) 
(list 1920.5625 113.7984)))
(apply 'command (append '("pline") coords '("c")))
(setq currobj (ssadd (entlast) currobj))
(setq coords (list 
(list 1920.5625 113.9414) 
(list 1994.585 114.0914) 
(list 1994.585 114.2684) 
(list 1920.5625 114.0184)))
(apply 'command (append '("pline") coords '("c")))
(setq currobj (ssadd (entlast) currobj))
(setq coords (list 
(list 1920.5625 114.1614) 
(list 1994.585 114.4114) 
(list 1994.585 114.5884) 
(list 1920.5625 114.2384)))
(apply 'command (append '("pline") coords '("c")))
(setq currobj (ssadd (entlast) currobj))
(setq coords (list 
(list 1920.5625 114.3814) 
(list 1994.585 114.7314) 
(list 1994.585 114.9084) 
(list 1920.5625 114.4584)))
(apply 'command (append '("pline") coords '("c")))
(setq currobj (ssadd (entlast) currobj))
(setq coords (list 
(list 1920.5625 114.6014) 
(list 1994.585 115.0514) 
(list 1994.585 115.2284) 
(list 1920.5625 114.6784)))
(apply 'command (append '("pline") coords '("c")))
(setq currobj (ssadd (entlast) currobj))
(setq coords (list 
(list 1920.5625 114.8214) 
(list 1994.585 115.3714) 
(list 1994.585 115.5484) 
(list 1920.5625 114.8984)))
(apply 'command (append '("pline") coords '("c")))
(setq currobj (ssadd (entlast) currobj))
(setq coords (list 
(list 1920.5625 115.0414) 
(list 1994.585 115.6914) 
(list 1994.585 115.8684) 
(list 1920.5625 115.1184)))
(apply 'command (append '("pline") coords '("c")))
(setq currobj (ssadd (entlast) currobj))
(setq coords (list 
(list 1919.4375 115.1184) 
(list 1845.415 115.8684) 
(list 1845.415 115.6914) 
(list 1919.4375 115.0414)))
(apply 'command (append '("pline") coords '("c")))
(setq currobj (ssadd (entlast) currobj))
(setq coords (list 
(list 1919.4375 114.8984) 
(list 1845.415 115.5484) 
(list 1845.415 115.3714) 
(list 1919.4375 114.8214)))
(apply 'command (append '("pline") coords '("c")))
(setq currobj (ssadd (entlast) currobj))
(setq coords (list 
(list 1919.4375 114.6784) 
(list 1845.415 115.2284) 
(list 1845.415 115.0514) 
(list 1919.4375 114.6014)))
(apply 'command (append '("pline") coords '("c")))
(setq currobj (ssadd (entlast) currobj))
(setq coords (list 
(list 1919.4375 114.4584) 
(list 1845.415 114.9084) 
(list 1845.415 114.7314) 
(list 1919.4375 114.3814)))
(apply 'command (append '("pline") coords '("c")))
(setq currobj (ssadd (entlast) currobj))
(setq coords (list 
(list 1919.4375 114.2384) 
(list 1845.415 114.5884) 
(list 1845.415 114.4114) 
(list 1919.4375 114.1614)))
(apply 'command (append '("pline") coords '("c")))
(setq currobj (ssadd (entlast) currobj))
(setq coords (list 
(list 1919.4375 114.0184) 
(list 1845.415 114.2684) 
(list 1845.415 114.0914) 
(list 1919.4375 113.9414)))
(apply 'command (append '("pline") coords '("c")))
(setq currobj (ssadd (entlast) currobj))
(setq coords (list 
(list 1919.4375 113.7984) 
(list 1845.415 113.9484) 
(list 1845.415 113.7714) 
(list 1919.4375 113.7214)))
(apply 'command (append '("pline") coords '("c")))
(setq currobj (ssadd (entlast) currobj))
(setq coords (list 
(list 1919.4375 113.5784) 
(list 1845.415 113.6284) 
(list 1845.415 113.4514) 
(list 1919.4375 113.5014)))
(apply 'command (append '("pline") coords '("c")))
(setq currobj (ssadd (entlast) currobj))
(setq coords (list 
(list 1919.4375 113.3584) 
(list 1845.415 113.3084) 
(list 1845.415 113.1314) 
(list 1919.4375 113.2814)))
(apply 'command (append '("pline") coords '("c")))
(setq currobj (ssadd (entlast) currobj))
(setq coords (list 
(list 1919.4375 113.1384) 
(list 1845.415 112.9884) 
(list 1845.415 112.8114) 
(list 1919.4375 113.0614)))
(apply 'command (append '("pline") coords '("c")))
(setq currobj (ssadd (entlast) currobj))
(setq coords (list 
(list 1919.4375 112.9184) 
(list 1845.415 112.6684) 
(list 1845.415 112.4914) 
(list 1919.4375 112.8414)))
(apply 'command (append '("pline") coords '("c")))
(setq currobj (ssadd (entlast) currobj))
(setq coords (list 
(list 1919.4375 112.6984) 
(list 1845.415 112.3484) 
(list 1845.415 112.1714) 
(list 1919.4375 112.6214)))
(apply 'command (append '("pline") coords '("c")))
(setq currobj (ssadd (entlast) currobj))
(setq coords (list 
(list 1919.4375 112.4784) 
(list 1845.415 112.0284) 
(list 1845.415 111.8514) 
(list 1919.4375 112.4014)))
(apply 'command (append '("pline") coords '("c")))
(setq currobj (ssadd (entlast) currobj))
(setq coords (list 
(list 1919.4375 112.2584) 
(list 1845.415 111.7084) 
(list 1845.415 111.5314) 
(list 1919.4375 112.1814)))
(apply 'command (append '("pline") coords '("c")))
(setq currobj (ssadd (entlast) currobj))
(setq coords (list 
(list 1919.4375 112.0384) 
(list 1845.415 111.3884) 
(list 1845.415 111.2114) 
(list 1919.4375 111.9614)))
(apply 'command (append '("pline") coords '("c")))
(setq currobj (ssadd (entlast) currobj))
(command "_layer" "set" "nitride" "")
(command "_layer" "set" "text" "")
(command "_circle" "1919.0625,100.8184" "0.075")
(command "_circle" "1919.0625,101.1184" "0.075")
(command "_circle" "1919.0625,101.4184" "0.075")
(command "_circle" "1919.0625,101.7184" "0.075")
(command "_circle" "1919.0625,102.0184" "0.075")
(command "_circle" "1918.7625,100.8184" "0.075")
(command "_circle" "1918.7625,101.1184" "0.075")
(command "_circle" "1918.7625,101.4184" "0.075")
(command "_circle" "1918.7625,101.7184" "0.075")
(command "_circle" "1918.7625,102.0184" "0.075")
(command "_circle" "1918.4625,100.8184" "0.075")
(command "_circle" "1918.4625,101.1184" "0.075")
(command "_circle" "1918.4625,101.4184" "0.075")
(command "_circle" "1918.4625,101.7184" "0.075")
(command "_circle" "1918.4625,102.0184" "0.075")
(command "_circle" "1918.1625,100.8184" "0.075")
(command "_circle" "1918.1625,101.1184" "0.075")
(command "_circle" "1918.1625,101.4184" "0.075")
(command "_circle" "1918.1625,101.7184" "0.075")
(command "_circle" "1918.1625,102.0184" "0.075")
(command "_circle" "1917.8625,100.8184" "0.075")
(command "_circle" "1917.8625,101.1184" "0.075")
(command "_circle" "1917.8625,101.4184" "0.075")
(command "_circle" "1917.8625,101.7184" "0.075")
(command "_circle" "1917.8625,102.0184" "0.075")
(command "_layer" "set" "nitride" "")
(setq coords (list 
(list 1920.2625 126.2614) 
(list 1920.2625 241.9061) 
(list 1919.7375 241.9061) 
(list 1919.7375 126.2614)))
(apply 'command (append '("pline") coords '("c")))
(setq currobj (ssadd (entlast) currobj))
(command "_layer" "set" "prebias" "")
(command "_rectangle" "1919.7375,126.2614" "1920.2625,241.9061")
(setq currobj (ssadd (entlast) currobj))
(command "_layer" "set" "nitride" "")
(setq coords (list 
(list 1920.2625 241.9061) 
(list 1920.5625 251.9061) 
(list 1920.5625 251.9061) 
(list 1920.5625 252.9061) 
(list 1994.585 252.1561) 
(list 1994.585 257.0991) 
(list 1920.5625 256.3491) 
(list 1920.5625 257.3491) 
(list 1920.5625 257.3491) 
(list 1920.2625 267.3491) 
(list 1919.7375 267.3491) 
(list 1919.4375 257.3491) 
(list 1919.4375 257.3491) 
(list 1919.4375 256.3491) 
(list 1845.415 257.0991) 
(list 1845.415 252.1561) 
(list 1919.4375 252.9061) 
(list 1919.4375 251.9061) 
(list 1919.4375 251.9061) 
(list 1919.7375 241.9061)))
(apply 'command (append '("pline") coords '("c")))
(setq currobj (ssadd (entlast) currobj))
(command "_layer" "set" "prebias" "")
(setq coords (list 
(list 1919.4375 241.9061) 
(list 1919.4375 252.9061) 
(list 1845.415 252.1561) 
(list 1845.415 257.0991) 
(list 1919.4375 256.3491) 
(list 1919.4375 267.3491) 
(list 1920.5625 267.3491) 
(list 1920.5625 256.3491) 
(list 1994.585 257.0991) 
(list 1994.585 252.1561) 
(list 1920.5625 252.9061) 
(list 1920.5625 241.9061)))
(apply 'command (append '("pline") coords '("c")))
(setq currobj (ssadd (entlast) currobj))
(command "_layer" "set" "nitride" "")
(command "_layer" "set" "fda1" "")
(setq coords (list 
(list 1920.5625 253.0491) 
(list 1994.585 252.2991) 
(list 1994.585 252.4761) 
(list 1920.5625 253.1261)))
(apply 'command (append '("pline") coords '("c")))
(setq currobj (ssadd (entlast) currobj))
(setq coords (list 
(list 1920.5625 253.2691) 
(list 1994.585 252.6191) 
(list 1994.585 252.7961) 
(list 1920.5625 253.3461)))
(apply 'command (append '("pline") coords '("c")))
(setq currobj (ssadd (entlast) currobj))
(setq coords (list 
(list 1920.5625 253.4891) 
(list 1994.585 252.9391) 
(list 1994.585 253.1161) 
(list 1920.5625 253.5661)))
(apply 'command (append '("pline") coords '("c")))
(setq currobj (ssadd (entlast) currobj))
(setq coords (list 
(list 1920.5625 253.7091) 
(list 1994.585 253.2591) 
(list 1994.585 253.4361) 
(list 1920.5625 253.7861)))
(apply 'command (append '("pline") coords '("c")))
(setq currobj (ssadd (entlast) currobj))
(setq coords (list 
(list 1920.5625 253.9291) 
(list 1994.585 253.5791) 
(list 1994.585 253.7561) 
(list 1920.5625 254.0061)))
(apply 'command (append '("pline") coords '("c")))
(setq currobj (ssadd (entlast) currobj))
(setq coords (list 
(list 1920.5625 254.1491) 
(list 1994.585 253.8991) 
(list 1994.585 254.0761) 
(list 1920.5625 254.2261)))
(apply 'command (append '("pline") coords '("c")))
(setq currobj (ssadd (entlast) currobj))
(setq coords (list 
(list 1920.5625 254.3691) 
(list 1994.585 254.2191) 
(list 1994.585 254.3961) 
(list 1920.5625 254.4461)))
(apply 'command (append '("pline") coords '("c")))
(setq currobj (ssadd (entlast) currobj))
(setq coords (list 
(list 1920.5625 254.5891) 
(list 1994.585 254.5391) 
(list 1994.585 254.7161) 
(list 1920.5625 254.6661)))
(apply 'command (append '("pline") coords '("c")))
(setq currobj (ssadd (entlast) currobj))
(setq coords (list 
(list 1920.5625 254.8091) 
(list 1994.585 254.8591) 
(list 1994.585 255.0361) 
(list 1920.5625 254.8861)))
(apply 'command (append '("pline") coords '("c")))
(setq currobj (ssadd (entlast) currobj))
(setq coords (list 
(list 1920.5625 255.0291) 
(list 1994.585 255.1791) 
(list 1994.585 255.3561) 
(list 1920.5625 255.1061)))
(apply 'command (append '("pline") coords '("c")))
(setq currobj (ssadd (entlast) currobj))
(setq coords (list 
(list 1920.5625 255.2491) 
(list 1994.585 255.4991) 
(list 1994.585 255.6761) 
(list 1920.5625 255.3261)))
(apply 'command (append '("pline") coords '("c")))
(setq currobj (ssadd (entlast) currobj))
(setq coords (list 
(list 1920.5625 255.4691) 
(list 1994.585 255.8191) 
(list 1994.585 255.9961) 
(list 1920.5625 255.5461)))
(apply 'command (append '("pline") coords '("c")))
(setq currobj (ssadd (entlast) currobj))
(setq coords (list 
(list 1920.5625 255.6891) 
(list 1994.585 256.1391) 
(list 1994.585 256.3161) 
(list 1920.5625 255.7661)))
(apply 'command (append '("pline") coords '("c")))
(setq currobj (ssadd (entlast) currobj))
(setq coords (list 
(list 1920.5625 255.9091) 
(list 1994.585 256.4591) 
(list 1994.585 256.6361) 
(list 1920.5625 255.9861)))
(apply 'command (append '("pline") coords '("c")))
(setq currobj (ssadd (entlast) currobj))
(setq coords (list 
(list 1920.5625 256.1291) 
(list 1994.585 256.7791) 
(list 1994.585 256.9561) 
(list 1920.5625 256.2061)))
(apply 'command (append '("pline") coords '("c")))
(setq currobj (ssadd (entlast) currobj))
(setq coords (list 
(list 1919.4375 256.2061) 
(list 1845.415 256.9561) 
(list 1845.415 256.7791) 
(list 1919.4375 256.1291)))
(apply 'command (append '("pline") coords '("c")))
(setq currobj (ssadd (entlast) currobj))
(setq coords (list 
(list 1919.4375 255.9861) 
(list 1845.415 256.6361) 
(list 1845.415 256.4591) 
(list 1919.4375 255.9091)))
(apply 'command (append '("pline") coords '("c")))
(setq currobj (ssadd (entlast) currobj))
(setq coords (list 
(list 1919.4375 255.7661) 
(list 1845.415 256.3161) 
(list 1845.415 256.1391) 
(list 1919.4375 255.6891)))
(apply 'command (append '("pline") coords '("c")))
(setq currobj (ssadd (entlast) currobj))
(setq coords (list 
(list 1919.4375 255.5461) 
(list 1845.415 255.9961) 
(list 1845.415 255.8191) 
(list 1919.4375 255.4691)))
(apply 'command (append '("pline") coords '("c")))
(setq currobj (ssadd (entlast) currobj))
(setq coords (list 
(list 1919.4375 255.3261) 
(list 1845.415 255.6761) 
(list 1845.415 255.4991) 
(list 1919.4375 255.2491)))
(apply 'command (append '("pline") coords '("c")))
(setq currobj (ssadd (entlast) currobj))
(setq coords (list 
(list 1919.4375 255.1061) 
(list 1845.415 255.3561) 
(list 1845.415 255.1791) 
(list 1919.4375 255.0291)))
(apply 'command (append '("pline") coords '("c")))
(setq currobj (ssadd (entlast) currobj))
(setq coords (list 
(list 1919.4375 254.8861) 
(list 1845.415 255.0361) 
(list 1845.415 254.8591) 
(list 1919.4375 254.8091)))
(apply 'command (append '("pline") coords '("c")))
(setq currobj (ssadd (entlast) currobj))
(setq coords (list 
(list 1919.4375 254.6661) 
(list 1845.415 254.7161) 
(list 1845.415 254.5391) 
(list 1919.4375 254.5891)))
(apply 'command (append '("pline") coords '("c")))
(setq currobj (ssadd (entlast) currobj))
(setq coords (list 
(list 1919.4375 254.4461) 
(list 1845.415 254.3961) 
(list 1845.415 254.2191) 
(list 1919.4375 254.3691)))
(apply 'command (append '("pline") coords '("c")))
(setq currobj (ssadd (entlast) currobj))
(setq coords (list 
(list 1919.4375 254.2261) 
(list 1845.415 254.0761) 
(list 1845.415 253.8991) 
(list 1919.4375 254.1491)))
(apply 'command (append '("pline") coords '("c")))
(setq currobj (ssadd (entlast) currobj))
(setq coords (list 
(list 1919.4375 254.0061) 
(list 1845.415 253.7561) 
(list 1845.415 253.5791) 
(list 1919.4375 253.9291)))
(apply 'command (append '("pline") coords '("c")))
(setq currobj (ssadd (entlast) currobj))
(setq coords (list 
(list 1919.4375 253.7861) 
(list 1845.415 253.4361) 
(list 1845.415 253.2591) 
(list 1919.4375 253.7091)))
(apply 'command (append '("pline") coords '("c")))
(setq currobj (ssadd (entlast) currobj))
(setq coords (list 
(list 1919.4375 253.5661) 
(list 1845.415 253.1161) 
(list 1845.415 252.9391) 
(list 1919.4375 253.4891)))
(apply 'command (append '("pline") coords '("c")))
(setq currobj (ssadd (entlast) currobj))
(setq coords (list 
(list 1919.4375 253.3461) 
(list 1845.415 252.7961) 
(list 1845.415 252.6191) 
(list 1919.4375 253.2691)))
(apply 'command (append '("pline") coords '("c")))
(setq currobj (ssadd (entlast) currobj))
(setq coords (list 
(list 1919.4375 253.1261) 
(list 1845.415 252.4761) 
(list 1845.415 252.2991) 
(list 1919.4375 253.0491)))
(apply 'command (append '("pline") coords '("c")))
(setq currobj (ssadd (entlast) currobj))
(command "_layer" "set" "nitride" "")
(command "_layer" "set" "text" "")
(command "_circle" "1919.0625,241.9061" "0.075")
(command "_circle" "1919.0625,242.2061" "0.075")
(command "_circle" "1919.0625,242.5061" "0.075")
(command "_circle" "1919.0625,242.8061" "0.075")
(command "_circle" "1919.0625,243.1061" "0.075")
(command "_circle" "1918.7625,241.9061" "0.075")
(command "_circle" "1918.7625,242.2061" "0.075")
(command "_circle" "1918.7625,242.5061" "0.075")
(command "_circle" "1918.7625,242.8061" "0.075")
(command "_circle" "1918.7625,243.1061" "0.075")
(command "_circle" "1918.4625,241.9061" "0.075")
(command "_circle" "1918.4625,242.2061" "0.075")
(command "_circle" "1918.4625,242.5061" "0.075")
(command "_circle" "1918.4625,242.8061" "0.075")
(command "_circle" "1918.4625,243.1061" "0.075")
(command "_circle" "1918.1625,241.9061" "0.075")
(command "_circle" "1918.1625,242.2061" "0.075")
(command "_circle" "1918.1625,242.5061" "0.075")
(command "_circle" "1918.1625,242.8061" "0.075")
(command "_circle" "1918.1625,243.1061" "0.075")
(command "_circle" "1917.8625,241.9061" "0.075")
(command "_circle" "1917.8625,242.2061" "0.075")
(command "_circle" "1917.8625,242.5061" "0.075")
(command "_circle" "1917.8625,242.8061" "0.075")
(command "_circle" "1917.8625,243.1061" "0.075")
(command "_layer" "set" "nitride" "")
(setq coords (list 
(list 1920.2625 267.3491) 
(list 1920.2625 382.9939) 
(list 1919.7375 382.9939) 
(list 1919.7375 267.3491)))
(apply 'command (append '("pline") coords '("c")))
(setq currobj (ssadd (entlast) currobj))
(command "_layer" "set" "prebias" "")
(command "_rectangle" "1919.7375,267.3491" "1920.2625,382.9939")
(setq currobj (ssadd (entlast) currobj))
(command "_layer" "set" "nitride" "")
(setq coords (list 
(list 1920.2625 382.9939) 
(list 1920.5625 392.9939) 
(list 1920.5625 392.9939) 
(list 1920.5625 393.9939) 
(list 1994.585 393.2439) 
(list 1994.585 398.1869) 
(list 1920.5625 397.4369) 
(list 1920.5625 398.4369) 
(list 1920.5625 398.4369) 
(list 1920.2625 408.4369) 
(list 1919.7375 408.4369) 
(list 1919.4375 398.4369) 
(list 1919.4375 398.4369) 
(list 1919.4375 397.4369) 
(list 1845.415 398.1869) 
(list 1845.415 393.2439) 
(list 1919.4375 393.9939) 
(list 1919.4375 392.9939) 
(list 1919.4375 392.9939) 
(list 1919.7375 382.9939)))
(apply 'command (append '("pline") coords '("c")))
(setq currobj (ssadd (entlast) currobj))
(command "_layer" "set" "prebias" "")
(setq coords (list 
(list 1919.4375 382.9939) 
(list 1919.4375 393.9939) 
(list 1845.415 393.2439) 
(list 1845.415 398.1869) 
(list 1919.4375 397.4369) 
(list 1919.4375 408.4369) 
(list 1920.5625 408.4369) 
(list 1920.5625 397.4369) 
(list 1994.585 398.1869) 
(list 1994.585 393.2439) 
(list 1920.5625 393.9939) 
(list 1920.5625 382.9939)))
(apply 'command (append '("pline") coords '("c")))
(setq currobj (ssadd (entlast) currobj))
(command "_layer" "set" "nitride" "")
(command "_layer" "set" "fda1" "")
(setq coords (list 
(list 1920.5625 394.1369) 
(list 1994.585 393.3869) 
(list 1994.585 393.5639) 
(list 1920.5625 394.2139)))
(apply 'command (append '("pline") coords '("c")))
(setq currobj (ssadd (entlast) currobj))
(setq coords (list 
(list 1920.5625 394.3569) 
(list 1994.585 393.7069) 
(list 1994.585 393.8839) 
(list 1920.5625 394.4339)))
(apply 'command (append '("pline") coords '("c")))
(setq currobj (ssadd (entlast) currobj))
(setq coords (list 
(list 1920.5625 394.5769) 
(list 1994.585 394.0269) 
(list 1994.585 394.2039) 
(list 1920.5625 394.6539)))
(apply 'command (append '("pline") coords '("c")))
(setq currobj (ssadd (entlast) currobj))
(setq coords (list 
(list 1920.5625 394.7969) 
(list 1994.585 394.3469) 
(list 1994.585 394.5239) 
(list 1920.5625 394.8739)))
(apply 'command (append '("pline") coords '("c")))
(setq currobj (ssadd (entlast) currobj))
(setq coords (list 
(list 1920.5625 395.0169) 
(list 1994.585 394.6669) 
(list 1994.585 394.8439) 
(list 1920.5625 395.0939)))
(apply 'command (append '("pline") coords '("c")))
(setq currobj (ssadd (entlast) currobj))
(setq coords (list 
(list 1920.5625 395.2369) 
(list 1994.585 394.9869) 
(list 1994.585 395.1639) 
(list 1920.5625 395.3139)))
(apply 'command (append '("pline") coords '("c")))
(setq currobj (ssadd (entlast) currobj))
(setq coords (list 
(list 1920.5625 395.4569) 
(list 1994.585 395.3069) 
(list 1994.585 395.4839) 
(list 1920.5625 395.5339)))
(apply 'command (append '("pline") coords '("c")))
(setq currobj (ssadd (entlast) currobj))
(setq coords (list 
(list 1920.5625 395.6769) 
(list 1994.585 395.6269) 
(list 1994.585 395.8039) 
(list 1920.5625 395.7539)))
(apply 'command (append '("pline") coords '("c")))
(setq currobj (ssadd (entlast) currobj))
(setq coords (list 
(list 1920.5625 395.8969) 
(list 1994.585 395.9469) 
(list 1994.585 396.1239) 
(list 1920.5625 395.9739)))
(apply 'command (append '("pline") coords '("c")))
(setq currobj (ssadd (entlast) currobj))
(setq coords (list 
(list 1920.5625 396.1169) 
(list 1994.585 396.2669) 
(list 1994.585 396.4439) 
(list 1920.5625 396.1939)))
(apply 'command (append '("pline") coords '("c")))
(setq currobj (ssadd (entlast) currobj))
(setq coords (list 
(list 1920.5625 396.3369) 
(list 1994.585 396.5869) 
(list 1994.585 396.7639) 
(list 1920.5625 396.4139)))
(apply 'command (append '("pline") coords '("c")))
(setq currobj (ssadd (entlast) currobj))
(setq coords (list 
(list 1920.5625 396.5569) 
(list 1994.585 396.9069) 
(list 1994.585 397.0839) 
(list 1920.5625 396.6339)))
(apply 'command (append '("pline") coords '("c")))
(setq currobj (ssadd (entlast) currobj))
(setq coords (list 
(list 1920.5625 396.7769) 
(list 1994.585 397.2269) 
(list 1994.585 397.4039) 
(list 1920.5625 396.8539)))
(apply 'command (append '("pline") coords '("c")))
(setq currobj (ssadd (entlast) currobj))
(setq coords (list 
(list 1920.5625 396.9969) 
(list 1994.585 397.5469) 
(list 1994.585 397.7239) 
(list 1920.5625 397.0739)))
(apply 'command (append '("pline") coords '("c")))
(setq currobj (ssadd (entlast) currobj))
(setq coords (list 
(list 1920.5625 397.2169) 
(list 1994.585 397.8669) 
(list 1994.585 398.0439) 
(list 1920.5625 397.2939)))
(apply 'command (append '("pline") coords '("c")))
(setq currobj (ssadd (entlast) currobj))
(setq coords (list 
(list 1919.4375 397.2939) 
(list 1845.415 398.0439) 
(list 1845.415 397.8669) 
(list 1919.4375 397.2169)))
(apply 'command (append '("pline") coords '("c")))
(setq currobj (ssadd (entlast) currobj))
(setq coords (list 
(list 1919.4375 397.0739) 
(list 1845.415 397.7239) 
(list 1845.415 397.5469) 
(list 1919.4375 396.9969)))
(apply 'command (append '("pline") coords '("c")))
(setq currobj (ssadd (entlast) currobj))
(setq coords (list 
(list 1919.4375 396.8539) 
(list 1845.415 397.4039) 
(list 1845.415 397.2269) 
(list 1919.4375 396.7769)))
(apply 'command (append '("pline") coords '("c")))
(setq currobj (ssadd (entlast) currobj))
(setq coords (list 
(list 1919.4375 396.6339) 
(list 1845.415 397.0839) 
(list 1845.415 396.9069) 
(list 1919.4375 396.5569)))
(apply 'command (append '("pline") coords '("c")))
(setq currobj (ssadd (entlast) currobj))
(setq coords (list 
(list 1919.4375 396.4139) 
(list 1845.415 396.7639) 
(list 1845.415 396.5869) 
(list 1919.4375 396.3369)))
(apply 'command (append '("pline") coords '("c")))
(setq currobj (ssadd (entlast) currobj))
(setq coords (list 
(list 1919.4375 396.1939) 
(list 1845.415 396.4439) 
(list 1845.415 396.2669) 
(list 1919.4375 396.1169)))
(apply 'command (append '("pline") coords '("c")))
(setq currobj (ssadd (entlast) currobj))
(setq coords (list 
(list 1919.4375 395.9739) 
(list 1845.415 396.1239) 
(list 1845.415 395.9469) 
(list 1919.4375 395.8969)))
(apply 'command (append '("pline") coords '("c")))
(setq currobj (ssadd (entlast) currobj))
(setq coords (list 
(list 1919.4375 395.7539) 
(list 1845.415 395.8039) 
(list 1845.415 395.6269) 
(list 1919.4375 395.6769)))
(apply 'command (append '("pline") coords '("c")))
(setq currobj (ssadd (entlast) currobj))
(setq coords (list 
(list 1919.4375 395.5339) 
(list 1845.415 395.4839) 
(list 1845.415 395.3069) 
(list 1919.4375 395.4569)))
(apply 'command (append '("pline") coords '("c")))
(setq currobj (ssadd (entlast) currobj))
(setq coords (list 
(list 1919.4375 395.3139) 
(list 1845.415 395.1639) 
(list 1845.415 394.9869) 
(list 1919.4375 395.2369)))
(apply 'command (append '("pline") coords '("c")))
(setq currobj (ssadd (entlast) currobj))
(setq coords (list 
(list 1919.4375 395.0939) 
(list 1845.415 394.8439) 
(list 1845.415 394.6669) 
(list 1919.4375 395.0169)))
(apply 'command (append '("pline") coords '("c")))
(setq currobj (ssadd (entlast) currobj))
(setq coords (list 
(list 1919.4375 394.8739) 
(list 1845.415 394.5239) 
(list 1845.415 394.3469) 
(list 1919.4375 394.7969)))
(apply 'command (append '("pline") coords '("c")))
(setq currobj (ssadd (entlast) currobj))
(setq coords (list 
(list 1919.4375 394.6539) 
(list 1845.415 394.2039) 
(list 1845.415 394.0269) 
(list 1919.4375 394.5769)))
(apply 'command (append '("pline") coords '("c")))
(setq currobj (ssadd (entlast) currobj))
(setq coords (list 
(list 1919.4375 394.4339) 
(list 1845.415 393.8839) 
(list 1845.415 393.7069) 
(list 1919.4375 394.3569)))
(apply 'command (append '("pline") coords '("c")))
(setq currobj (ssadd (entlast) currobj))
(setq coords (list 
(list 1919.4375 394.2139) 
(list 1845.415 393.5639) 
(list 1845.415 393.3869) 
(list 1919.4375 394.1369)))
(apply 'command (append '("pline") coords '("c")))
(setq currobj (ssadd (entlast) currobj))
(command "_layer" "set" "nitride" "")
(command "_layer" "set" "text" "")
(command "_circle" "1919.0625,382.9939" "0.075")
(command "_circle" "1919.0625,383.2939" "0.075")
(command "_circle" "1919.0625,383.5939" "0.075")
(command "_circle" "1919.0625,383.8939" "0.075")
(command "_circle" "1919.0625,384.1939" "0.075")
(command "_circle" "1918.7625,382.9939" "0.075")
(command "_circle" "1918.7625,383.2939" "0.075")
(command "_circle" "1918.7625,383.5939" "0.075")
(command "_circle" "1918.7625,383.8939" "0.075")
(command "_circle" "1918.7625,384.1939" "0.075")
(command "_circle" "1918.4625,382.9939" "0.075")
(command "_circle" "1918.4625,383.2939" "0.075")
(command "_circle" "1918.4625,383.5939" "0.075")
(command "_circle" "1918.4625,383.8939" "0.075")
(command "_circle" "1918.4625,384.1939" "0.075")
(command "_circle" "1918.1625,382.9939" "0.075")
(command "_circle" "1918.1625,383.2939" "0.075")
(command "_circle" "1918.1625,383.5939" "0.075")
(command "_circle" "1918.1625,383.8939" "0.075")
(command "_circle" "1918.1625,384.1939" "0.075")
(command "_circle" "1917.8625,382.9939" "0.075")
(command "_circle" "1917.8625,383.2939" "0.075")
(command "_circle" "1917.8625,383.5939" "0.075")
(command "_circle" "1917.8625,383.8939" "0.075")
(command "_circle" "1917.8625,384.1939" "0.075")
(command "_layer" "set" "nitride" "")
(setq coords (list 
(list 1920.2625 408.4369) 
(list 1920.2625 524.0816) 
(list 1919.7375 524.0816) 
(list 1919.7375 408.4369)))
(apply 'command (append '("pline") coords '("c")))
(setq currobj (ssadd (entlast) currobj))
(command "_layer" "set" "prebias" "")
(command "_rectangle" "1919.7375,408.4369" "1920.2625,524.0816")
(setq currobj (ssadd (entlast) currobj))
(command "_layer" "set" "nitride" "")
(setq coords (list 
(list 1920.2625 524.0816) 
(list 1920.5625 534.0816) 
(list 1920.5625 534.0816) 
(list 1920.5625 535.0816) 
(list 1994.585 534.3316) 
(list 1994.585 539.2746) 
(list 1920.5625 538.5246) 
(list 1920.5625 539.5246) 
(list 1920.5625 539.5246) 
(list 1920.2625 549.5246) 
(list 1919.7375 549.5246) 
(list 1919.4375 539.5246) 
(list 1919.4375 539.5246) 
(list 1919.4375 538.5246) 
(list 1845.415 539.2746) 
(list 1845.415 534.3316) 
(list 1919.4375 535.0816) 
(list 1919.4375 534.0816) 
(list 1919.4375 534.0816) 
(list 1919.7375 524.0816)))
(apply 'command (append '("pline") coords '("c")))
(setq currobj (ssadd (entlast) currobj))
(command "_layer" "set" "prebias" "")
(setq coords (list 
(list 1919.4375 524.0816) 
(list 1919.4375 535.0816) 
(list 1845.415 534.3316) 
(list 1845.415 539.2746) 
(list 1919.4375 538.5246) 
(list 1919.4375 549.5246) 
(list 1920.5625 549.5246) 
(list 1920.5625 538.5246) 
(list 1994.585 539.2746) 
(list 1994.585 534.3316) 
(list 1920.5625 535.0816) 
(list 1920.5625 524.0816)))
(apply 'command (append '("pline") coords '("c")))
(setq currobj (ssadd (entlast) currobj))
(command "_layer" "set" "nitride" "")
(command "_layer" "set" "fda1" "")
(setq coords (list 
(list 1920.5625 535.2246) 
(list 1994.585 534.4746) 
(list 1994.585 534.6516) 
(list 1920.5625 535.3016)))
(apply 'command (append '("pline") coords '("c")))
(setq currobj (ssadd (entlast) currobj))
(setq coords (list 
(list 1920.5625 535.4446) 
(list 1994.585 534.7946) 
(list 1994.585 534.9716) 
(list 1920.5625 535.5216)))
(apply 'command (append '("pline") coords '("c")))
(setq currobj (ssadd (entlast) currobj))
(setq coords (list 
(list 1920.5625 535.6646) 
(list 1994.585 535.1146) 
(list 1994.585 535.2916) 
(list 1920.5625 535.7416)))
(apply 'command (append '("pline") coords '("c")))
(setq currobj (ssadd (entlast) currobj))
(setq coords (list 
(list 1920.5625 535.8846) 
(list 1994.585 535.4346) 
(list 1994.585 535.6116) 
(list 1920.5625 535.9616)))
(apply 'command (append '("pline") coords '("c")))
(setq currobj (ssadd (entlast) currobj))
(setq coords (list 
(list 1920.5625 536.1046) 
(list 1994.585 535.7546) 
(list 1994.585 535.9316) 
(list 1920.5625 536.1816)))
(apply 'command (append '("pline") coords '("c")))
(setq currobj (ssadd (entlast) currobj))
(setq coords (list 
(list 1920.5625 536.3246) 
(list 1994.585 536.0746) 
(list 1994.585 536.2516) 
(list 1920.5625 536.4016)))
(apply 'command (append '("pline") coords '("c")))
(setq currobj (ssadd (entlast) currobj))
(setq coords (list 
(list 1920.5625 536.5446) 
(list 1994.585 536.3946) 
(list 1994.585 536.5716) 
(list 1920.5625 536.6216)))
(apply 'command (append '("pline") coords '("c")))
(setq currobj (ssadd (entlast) currobj))
(setq coords (list 
(list 1920.5625 536.7646) 
(list 1994.585 536.7146) 
(list 1994.585 536.8916) 
(list 1920.5625 536.8416)))
(apply 'command (append '("pline") coords '("c")))
(setq currobj (ssadd (entlast) currobj))
(setq coords (list 
(list 1920.5625 536.9846) 
(list 1994.585 537.0346) 
(list 1994.585 537.2116) 
(list 1920.5625 537.0616)))
(apply 'command (append '("pline") coords '("c")))
(setq currobj (ssadd (entlast) currobj))
(setq coords (list 
(list 1920.5625 537.2046) 
(list 1994.585 537.3546) 
(list 1994.585 537.5316) 
(list 1920.5625 537.2816)))
(apply 'command (append '("pline") coords '("c")))
(setq currobj (ssadd (entlast) currobj))
(setq coords (list 
(list 1920.5625 537.4246) 
(list 1994.585 537.6746) 
(list 1994.585 537.8516) 
(list 1920.5625 537.5016)))
(apply 'command (append '("pline") coords '("c")))
(setq currobj (ssadd (entlast) currobj))
(setq coords (list 
(list 1920.5625 537.6446) 
(list 1994.585 537.9946) 
(list 1994.585 538.1716) 
(list 1920.5625 537.7216)))
(apply 'command (append '("pline") coords '("c")))
(setq currobj (ssadd (entlast) currobj))
(setq coords (list 
(list 1920.5625 537.8646) 
(list 1994.585 538.3146) 
(list 1994.585 538.4916) 
(list 1920.5625 537.9416)))
(apply 'command (append '("pline") coords '("c")))
(setq currobj (ssadd (entlast) currobj))
(setq coords (list 
(list 1920.5625 538.0846) 
(list 1994.585 538.6346) 
(list 1994.585 538.8116) 
(list 1920.5625 538.1616)))
(apply 'command (append '("pline") coords '("c")))
(setq currobj (ssadd (entlast) currobj))
(setq coords (list 
(list 1920.5625 538.3046) 
(list 1994.585 538.9546) 
(list 1994.585 539.1316) 
(list 1920.5625 538.3816)))
(apply 'command (append '("pline") coords '("c")))
(setq currobj (ssadd (entlast) currobj))
(setq coords (list 
(list 1919.4375 538.3816) 
(list 1845.415 539.1316) 
(list 1845.415 538.9546) 
(list 1919.4375 538.3046)))
(apply 'command (append '("pline") coords '("c")))
(setq currobj (ssadd (entlast) currobj))
(setq coords (list 
(list 1919.4375 538.1616) 
(list 1845.415 538.8116) 
(list 1845.415 538.6346) 
(list 1919.4375 538.0846)))
(apply 'command (append '("pline") coords '("c")))
(setq currobj (ssadd (entlast) currobj))
(setq coords (list 
(list 1919.4375 537.9416) 
(list 1845.415 538.4916) 
(list 1845.415 538.3146) 
(list 1919.4375 537.8646)))
(apply 'command (append '("pline") coords '("c")))
(setq currobj (ssadd (entlast) currobj))
(setq coords (list 
(list 1919.4375 537.7216) 
(list 1845.415 538.1716) 
(list 1845.415 537.9946) 
(list 1919.4375 537.6446)))
(apply 'command (append '("pline") coords '("c")))
(setq currobj (ssadd (entlast) currobj))
(setq coords (list 
(list 1919.4375 537.5016) 
(list 1845.415 537.8516) 
(list 1845.415 537.6746) 
(list 1919.4375 537.4246)))
(apply 'command (append '("pline") coords '("c")))
(setq currobj (ssadd (entlast) currobj))
(setq coords (list 
(list 1919.4375 537.2816) 
(list 1845.415 537.5316) 
(list 1845.415 537.3546) 
(list 1919.4375 537.2046)))
(apply 'command (append '("pline") coords '("c")))
(setq currobj (ssadd (entlast) currobj))
(setq coords (list 
(list 1919.4375 537.0616) 
(list 1845.415 537.2116) 
(list 1845.415 537.0346) 
(list 1919.4375 536.9846)))
(apply 'command (append '("pline") coords '("c")))
(setq currobj (ssadd (entlast) currobj))
(setq coords (list 
(list 1919.4375 536.8416) 
(list 1845.415 536.8916) 
(list 1845.415 536.7146) 
(list 1919.4375 536.7646)))
(apply 'command (append '("pline") coords '("c")))
(setq currobj (ssadd (entlast) currobj))
(setq coords (list 
(list 1919.4375 536.6216) 
(list 1845.415 536.5716) 
(list 1845.415 536.3946) 
(list 1919.4375 536.5446)))
(apply 'command (append '("pline") coords '("c")))
(setq currobj (ssadd (entlast) currobj))
(setq coords (list 
(list 1919.4375 536.4016) 
(list 1845.415 536.2516) 
(list 1845.415 536.0746) 
(list 1919.4375 536.3246)))
(apply 'command (append '("pline") coords '("c")))
(setq currobj (ssadd (entlast) currobj))
(setq coords (list 
(list 1919.4375 536.1816) 
(list 1845.415 535.9316) 
(list 1845.415 535.7546) 
(list 1919.4375 536.1046)))
(apply 'command (append '("pline") coords '("c")))
(setq currobj (ssadd (entlast) currobj))
(setq coords (list 
(list 1919.4375 535.9616) 
(list 1845.415 535.6116) 
(list 1845.415 535.4346) 
(list 1919.4375 535.8846)))
(apply 'command (append '("pline") coords '("c")))
(setq currobj (ssadd (entlast) currobj))
(setq coords (list 
(list 1919.4375 535.7416) 
(list 1845.415 535.2916) 
(list 1845.415 535.1146) 
(list 1919.4375 535.6646)))
(apply 'command (append '("pline") coords '("c")))
(setq currobj (ssadd (entlast) currobj))
(setq coords (list 
(list 1919.4375 535.5216) 
(list 1845.415 534.9716) 
(list 1845.415 534.7946) 
(list 1919.4375 535.4446)))
(apply 'command (append '("pline") coords '("c")))
(setq currobj (ssadd (entlast) currobj))
(setq coords (list 
(list 1919.4375 535.3016) 
(list 1845.415 534.6516) 
(list 1845.415 534.4746) 
(list 1919.4375 535.2246)))
(apply 'command (append '("pline") coords '("c")))
(setq currobj (ssadd (entlast) currobj))
(command "_layer" "set" "nitride" "")
(command "_layer" "set" "text" "")
(command "_circle" "1919.0625,524.0816" "0.075")
(command "_circle" "1919.0625,524.3816" "0.075")
(command "_circle" "1919.0625,524.6816" "0.075")
(command "_circle" "1919.0625,524.9816" "0.075")
(command "_circle" "1919.0625,525.2816" "0.075")
(command "_circle" "1918.7625,524.0816" "0.075")
(command "_circle" "1918.7625,524.3816" "0.075")
(command "_circle" "1918.7625,524.6816" "0.075")
(command "_circle" "1918.7625,524.9816" "0.075")
(command "_circle" "1918.7625,525.2816" "0.075")
(command "_circle" "1918.4625,524.0816" "0.075")
(command "_circle" "1918.4625,524.3816" "0.075")
(command "_circle" "1918.4625,524.6816" "0.075")
(command "_circle" "1918.4625,524.9816" "0.075")
(command "_circle" "1918.4625,525.2816" "0.075")
(command "_circle" "1918.1625,524.0816" "0.075")
(command "_circle" "1918.1625,524.3816" "0.075")
(command "_circle" "1918.1625,524.6816" "0.075")
(command "_circle" "1918.1625,524.9816" "0.075")
(command "_circle" "1918.1625,525.2816" "0.075")
(command "_circle" "1917.8625,524.0816" "0.075")
(command "_circle" "1917.8625,524.3816" "0.075")
(command "_circle" "1917.8625,524.6816" "0.075")
(command "_circle" "1917.8625,524.9816" "0.075")
(command "_circle" "1917.8625,525.2816" "0.075")
(command "_layer" "set" "nitride" "")
(setq coords (list 
(list 1920.2625 549.5246) 
(list 1920.2625 665.1693) 
(list 1919.7375 665.1693) 
(list 1919.7375 549.5246)))
(apply 'command (append '("pline") coords '("c")))
(setq currobj (ssadd (entlast) currobj))
(command "_layer" "set" "prebias" "")
(command "_rectangle" "1919.7375,549.5246" "1920.2625,665.1693")
(setq currobj (ssadd (entlast) currobj))
(command "_layer" "set" "nitride" "")
(setq coords (list 
(list 1920.2625 665.1693) 
(list 1920.5625 675.1693) 
(list 1920.5625 675.1693) 
(list 1920.5625 676.1693) 
(list 1994.585 675.4193) 
(list 1994.585 680.3623) 
(list 1920.5625 679.6123) 
(list 1920.5625 680.6123) 
(list 1920.5625 680.6123) 
(list 1920.2625 690.6123) 
(list 1919.7375 690.6123) 
(list 1919.4375 680.6123) 
(list 1919.4375 680.6123) 
(list 1919.4375 679.6123) 
(list 1845.415 680.3623) 
(list 1845.415 675.4193) 
(list 1919.4375 676.1693) 
(list 1919.4375 675.1693) 
(list 1919.4375 675.1693) 
(list 1919.7375 665.1693)))
(apply 'command (append '("pline") coords '("c")))
(setq currobj (ssadd (entlast) currobj))
(command "_layer" "set" "prebias" "")
(setq coords (list 
(list 1919.4375 665.1693) 
(list 1919.4375 676.1693) 
(list 1845.415 675.4193) 
(list 1845.415 680.3623) 
(list 1919.4375 679.6123) 
(list 1919.4375 690.6123) 
(list 1920.5625 690.6123) 
(list 1920.5625 679.6123) 
(list 1994.585 680.3623) 
(list 1994.585 675.4193) 
(list 1920.5625 676.1693) 
(list 1920.5625 665.1693)))
(apply 'command (append '("pline") coords '("c")))
(setq currobj (ssadd (entlast) currobj))
(command "_layer" "set" "nitride" "")
(command "_layer" "set" "fda1" "")
(setq coords (list 
(list 1920.5625 676.3123) 
(list 1994.585 675.5623) 
(list 1994.585 675.7393) 
(list 1920.5625 676.3893)))
(apply 'command (append '("pline") coords '("c")))
(setq currobj (ssadd (entlast) currobj))
(setq coords (list 
(list 1920.5625 676.5323) 
(list 1994.585 675.8823) 
(list 1994.585 676.0593) 
(list 1920.5625 676.6093)))
(apply 'command (append '("pline") coords '("c")))
(setq currobj (ssadd (entlast) currobj))
(setq coords (list 
(list 1920.5625 676.7523) 
(list 1994.585 676.2023) 
(list 1994.585 676.3793) 
(list 1920.5625 676.8293)))
(apply 'command (append '("pline") coords '("c")))
(setq currobj (ssadd (entlast) currobj))
(setq coords (list 
(list 1920.5625 676.9723) 
(list 1994.585 676.5223) 
(list 1994.585 676.6993) 
(list 1920.5625 677.0493)))
(apply 'command (append '("pline") coords '("c")))
(setq currobj (ssadd (entlast) currobj))
(setq coords (list 
(list 1920.5625 677.1923) 
(list 1994.585 676.8423) 
(list 1994.585 677.0193) 
(list 1920.5625 677.2693)))
(apply 'command (append '("pline") coords '("c")))
(setq currobj (ssadd (entlast) currobj))
(setq coords (list 
(list 1920.5625 677.4123) 
(list 1994.585 677.1623) 
(list 1994.585 677.3393) 
(list 1920.5625 677.4893)))
(apply 'command (append '("pline") coords '("c")))
(setq currobj (ssadd (entlast) currobj))
(setq coords (list 
(list 1920.5625 677.6323) 
(list 1994.585 677.4823) 
(list 1994.585 677.6593) 
(list 1920.5625 677.7093)))
(apply 'command (append '("pline") coords '("c")))
(setq currobj (ssadd (entlast) currobj))
(setq coords (list 
(list 1920.5625 677.8523) 
(list 1994.585 677.8023) 
(list 1994.585 677.9793) 
(list 1920.5625 677.9293)))
(apply 'command (append '("pline") coords '("c")))
(setq currobj (ssadd (entlast) currobj))
(setq coords (list 
(list 1920.5625 678.0723) 
(list 1994.585 678.1223) 
(list 1994.585 678.2993) 
(list 1920.5625 678.1493)))
(apply 'command (append '("pline") coords '("c")))
(setq currobj (ssadd (entlast) currobj))
(setq coords (list 
(list 1920.5625 678.2923) 
(list 1994.585 678.4423) 
(list 1994.585 678.6193) 
(list 1920.5625 678.3693)))
(apply 'command (append '("pline") coords '("c")))
(setq currobj (ssadd (entlast) currobj))
(setq coords (list 
(list 1920.5625 678.5123) 
(list 1994.585 678.7623) 
(list 1994.585 678.9393) 
(list 1920.5625 678.5893)))
(apply 'command (append '("pline") coords '("c")))
(setq currobj (ssadd (entlast) currobj))
(setq coords (list 
(list 1920.5625 678.7323) 
(list 1994.585 679.0823) 
(list 1994.585 679.2593) 
(list 1920.5625 678.8093)))
(apply 'command (append '("pline") coords '("c")))
(setq currobj (ssadd (entlast) currobj))
(setq coords (list 
(list 1920.5625 678.9523) 
(list 1994.585 679.4023) 
(list 1994.585 679.5793) 
(list 1920.5625 679.0293)))
(apply 'command (append '("pline") coords '("c")))
(setq currobj (ssadd (entlast) currobj))
(setq coords (list 
(list 1920.5625 679.1723) 
(list 1994.585 679.7223) 
(list 1994.585 679.8993) 
(list 1920.5625 679.2493)))
(apply 'command (append '("pline") coords '("c")))
(setq currobj (ssadd (entlast) currobj))
(setq coords (list 
(list 1920.5625 679.3923) 
(list 1994.585 680.0423) 
(list 1994.585 680.2193) 
(list 1920.5625 679.4693)))
(apply 'command (append '("pline") coords '("c")))
(setq currobj (ssadd (entlast) currobj))
(setq coords (list 
(list 1919.4375 679.4693) 
(list 1845.415 680.2193) 
(list 1845.415 680.0423) 
(list 1919.4375 679.3923)))
(apply 'command (append '("pline") coords '("c")))
(setq currobj (ssadd (entlast) currobj))
(setq coords (list 
(list 1919.4375 679.2493) 
(list 1845.415 679.8993) 
(list 1845.415 679.7223) 
(list 1919.4375 679.1723)))
(apply 'command (append '("pline") coords '("c")))
(setq currobj (ssadd (entlast) currobj))
(setq coords (list 
(list 1919.4375 679.0293) 
(list 1845.415 679.5793) 
(list 1845.415 679.4023) 
(list 1919.4375 678.9523)))
(apply 'command (append '("pline") coords '("c")))
(setq currobj (ssadd (entlast) currobj))
(setq coords (list 
(list 1919.4375 678.8093) 
(list 1845.415 679.2593) 
(list 1845.415 679.0823) 
(list 1919.4375 678.7323)))
(apply 'command (append '("pline") coords '("c")))
(setq currobj (ssadd (entlast) currobj))
(setq coords (list 
(list 1919.4375 678.5893) 
(list 1845.415 678.9393) 
(list 1845.415 678.7623) 
(list 1919.4375 678.5123)))
(apply 'command (append '("pline") coords '("c")))
(setq currobj (ssadd (entlast) currobj))
(setq coords (list 
(list 1919.4375 678.3693) 
(list 1845.415 678.6193) 
(list 1845.415 678.4423) 
(list 1919.4375 678.2923)))
(apply 'command (append '("pline") coords '("c")))
(setq currobj (ssadd (entlast) currobj))
(setq coords (list 
(list 1919.4375 678.1493) 
(list 1845.415 678.2993) 
(list 1845.415 678.1223) 
(list 1919.4375 678.0723)))
(apply 'command (append '("pline") coords '("c")))
(setq currobj (ssadd (entlast) currobj))
(setq coords (list 
(list 1919.4375 677.9293) 
(list 1845.415 677.9793) 
(list 1845.415 677.8023) 
(list 1919.4375 677.8523)))
(apply 'command (append '("pline") coords '("c")))
(setq currobj (ssadd (entlast) currobj))
(setq coords (list 
(list 1919.4375 677.7093) 
(list 1845.415 677.6593) 
(list 1845.415 677.4823) 
(list 1919.4375 677.6323)))
(apply 'command (append '("pline") coords '("c")))
(setq currobj (ssadd (entlast) currobj))
(setq coords (list 
(list 1919.4375 677.4893) 
(list 1845.415 677.3393) 
(list 1845.415 677.1623) 
(list 1919.4375 677.4123)))
(apply 'command (append '("pline") coords '("c")))
(setq currobj (ssadd (entlast) currobj))
(setq coords (list 
(list 1919.4375 677.2693) 
(list 1845.415 677.0193) 
(list 1845.415 676.8423) 
(list 1919.4375 677.1923)))
(apply 'command (append '("pline") coords '("c")))
(setq currobj (ssadd (entlast) currobj))
(setq coords (list 
(list 1919.4375 677.0493) 
(list 1845.415 676.6993) 
(list 1845.415 676.5223) 
(list 1919.4375 676.9723)))
(apply 'command (append '("pline") coords '("c")))
(setq currobj (ssadd (entlast) currobj))
(setq coords (list 
(list 1919.4375 676.8293) 
(list 1845.415 676.3793) 
(list 1845.415 676.2023) 
(list 1919.4375 676.7523)))
(apply 'command (append '("pline") coords '("c")))
(setq currobj (ssadd (entlast) currobj))
(setq coords (list 
(list 1919.4375 676.6093) 
(list 1845.415 676.0593) 
(list 1845.415 675.8823) 
(list 1919.4375 676.5323)))
(apply 'command (append '("pline") coords '("c")))
(setq currobj (ssadd (entlast) currobj))
(setq coords (list 
(list 1919.4375 676.3893) 
(list 1845.415 675.7393) 
(list 1845.415 675.5623) 
(list 1919.4375 676.3123)))
(apply 'command (append '("pline") coords '("c")))
(setq currobj (ssadd (entlast) currobj))
(command "_layer" "set" "nitride" "")
(command "_layer" "set" "text" "")
(command "_circle" "1919.0625,665.1693" "0.075")
(command "_circle" "1919.0625,665.4693" "0.075")
(command "_circle" "1919.0625,665.7693" "0.075")
(command "_circle" "1919.0625,666.0693" "0.075")
(command "_circle" "1919.0625,666.3693" "0.075")
(command "_circle" "1918.7625,665.1693" "0.075")
(command "_circle" "1918.7625,665.4693" "0.075")
(command "_circle" "1918.7625,665.7693" "0.075")
(command "_circle" "1918.7625,666.0693" "0.075")
(command "_circle" "1918.7625,666.3693" "0.075")
(command "_circle" "1918.4625,665.1693" "0.075")
(command "_circle" "1918.4625,665.4693" "0.075")
(command "_circle" "1918.4625,665.7693" "0.075")
(command "_circle" "1918.4625,666.0693" "0.075")
(command "_circle" "1918.4625,666.3693" "0.075")
(command "_circle" "1918.1625,665.1693" "0.075")
(command "_circle" "1918.1625,665.4693" "0.075")
(command "_circle" "1918.1625,665.7693" "0.075")
(command "_circle" "1918.1625,666.0693" "0.075")
(command "_circle" "1918.1625,666.3693" "0.075")
(command "_circle" "1917.8625,665.1693" "0.075")
(command "_circle" "1917.8625,665.4693" "0.075")
(command "_circle" "1917.8625,665.7693" "0.075")
(command "_circle" "1917.8625,666.0693" "0.075")
(command "_circle" "1917.8625,666.3693" "0.075")
(command "_layer" "set" "nitride" "")
(setq coords (list 
(list 1920.2625 690.6123) 
(list 1920.2625 806.257) 
(list 1919.7375 806.257) 
(list 1919.7375 690.6123)))
(apply 'command (append '("pline") coords '("c")))
(setq currobj (ssadd (entlast) currobj))
(command "_layer" "set" "prebias" "")
(command "_rectangle" "1919.7375,690.6123" "1920.2625,806.257")
(setq currobj (ssadd (entlast) currobj))
(command "_layer" "set" "nitride" "")
(setq coords (list 
(list 1920.2625 806.257) 
(list 1920.5625 816.257) 
(list 1920.5625 816.257) 
(list 1920.5625 817.257) 
(list 1994.585 816.507) 
(list 1994.585 821.45) 
(list 1920.5625 820.7) 
(list 1920.5625 821.7) 
(list 1920.5625 821.7) 
(list 1920.2625 831.7) 
(list 1919.7375 831.7) 
(list 1919.4375 821.7) 
(list 1919.4375 821.7) 
(list 1919.4375 820.7) 
(list 1845.415 821.45) 
(list 1845.415 816.507) 
(list 1919.4375 817.257) 
(list 1919.4375 816.257) 
(list 1919.4375 816.257) 
(list 1919.7375 806.257)))
(apply 'command (append '("pline") coords '("c")))
(setq currobj (ssadd (entlast) currobj))
(command "_layer" "set" "prebias" "")
(setq coords (list 
(list 1919.4375 806.257) 
(list 1919.4375 817.257) 
(list 1845.415 816.507) 
(list 1845.415 821.45) 
(list 1919.4375 820.7) 
(list 1919.4375 831.7) 
(list 1920.5625 831.7) 
(list 1920.5625 820.7) 
(list 1994.585 821.45) 
(list 1994.585 816.507) 
(list 1920.5625 817.257) 
(list 1920.5625 806.257)))
(apply 'command (append '("pline") coords '("c")))
(setq currobj (ssadd (entlast) currobj))
(command "_layer" "set" "nitride" "")
(command "_layer" "set" "fda1" "")
(setq coords (list 
(list 1920.5625 817.4) 
(list 1994.585 816.65) 
(list 1994.585 816.827) 
(list 1920.5625 817.477)))
(apply 'command (append '("pline") coords '("c")))
(setq currobj (ssadd (entlast) currobj))
(setq coords (list 
(list 1920.5625 817.62) 
(list 1994.585 816.97) 
(list 1994.585 817.147) 
(list 1920.5625 817.697)))
(apply 'command (append '("pline") coords '("c")))
(setq currobj (ssadd (entlast) currobj))
(setq coords (list 
(list 1920.5625 817.84) 
(list 1994.585 817.29) 
(list 1994.585 817.467) 
(list 1920.5625 817.917)))
(apply 'command (append '("pline") coords '("c")))
(setq currobj (ssadd (entlast) currobj))
(setq coords (list 
(list 1920.5625 818.06) 
(list 1994.585 817.61) 
(list 1994.585 817.787) 
(list 1920.5625 818.137)))
(apply 'command (append '("pline") coords '("c")))
(setq currobj (ssadd (entlast) currobj))
(setq coords (list 
(list 1920.5625 818.28) 
(list 1994.585 817.93) 
(list 1994.585 818.107) 
(list 1920.5625 818.357)))
(apply 'command (append '("pline") coords '("c")))
(setq currobj (ssadd (entlast) currobj))
(setq coords (list 
(list 1920.5625 818.5) 
(list 1994.585 818.25) 
(list 1994.585 818.427) 
(list 1920.5625 818.577)))
(apply 'command (append '("pline") coords '("c")))
(setq currobj (ssadd (entlast) currobj))
(setq coords (list 
(list 1920.5625 818.72) 
(list 1994.585 818.57) 
(list 1994.585 818.747) 
(list 1920.5625 818.797)))
(apply 'command (append '("pline") coords '("c")))
(setq currobj (ssadd (entlast) currobj))
(setq coords (list 
(list 1920.5625 818.94) 
(list 1994.585 818.89) 
(list 1994.585 819.067) 
(list 1920.5625 819.017)))
(apply 'command (append '("pline") coords '("c")))
(setq currobj (ssadd (entlast) currobj))
(setq coords (list 
(list 1920.5625 819.16) 
(list 1994.585 819.21) 
(list 1994.585 819.387) 
(list 1920.5625 819.237)))
(apply 'command (append '("pline") coords '("c")))
(setq currobj (ssadd (entlast) currobj))
(setq coords (list 
(list 1920.5625 819.38) 
(list 1994.585 819.53) 
(list 1994.585 819.707) 
(list 1920.5625 819.457)))
(apply 'command (append '("pline") coords '("c")))
(setq currobj (ssadd (entlast) currobj))
(setq coords (list 
(list 1920.5625 819.6) 
(list 1994.585 819.85) 
(list 1994.585 820.027) 
(list 1920.5625 819.677)))
(apply 'command (append '("pline") coords '("c")))
(setq currobj (ssadd (entlast) currobj))
(setq coords (list 
(list 1920.5625 819.82) 
(list 1994.585 820.17) 
(list 1994.585 820.347) 
(list 1920.5625 819.897)))
(apply 'command (append '("pline") coords '("c")))
(setq currobj (ssadd (entlast) currobj))
(setq coords (list 
(list 1920.5625 820.04) 
(list 1994.585 820.49) 
(list 1994.585 820.667) 
(list 1920.5625 820.117)))
(apply 'command (append '("pline") coords '("c")))
(setq currobj (ssadd (entlast) currobj))
(setq coords (list 
(list 1920.5625 820.26) 
(list 1994.585 820.81) 
(list 1994.585 820.987) 
(list 1920.5625 820.337)))
(apply 'command (append '("pline") coords '("c")))
(setq currobj (ssadd (entlast) currobj))
(setq coords (list 
(list 1920.5625 820.48) 
(list 1994.585 821.13) 
(list 1994.585 821.307) 
(list 1920.5625 820.557)))
(apply 'command (append '("pline") coords '("c")))
(setq currobj (ssadd (entlast) currobj))
(setq coords (list 
(list 1919.4375 820.557) 
(list 1845.415 821.307) 
(list 1845.415 821.13) 
(list 1919.4375 820.48)))
(apply 'command (append '("pline") coords '("c")))
(setq currobj (ssadd (entlast) currobj))
(setq coords (list 
(list 1919.4375 820.337) 
(list 1845.415 820.987) 
(list 1845.415 820.81) 
(list 1919.4375 820.26)))
(apply 'command (append '("pline") coords '("c")))
(setq currobj (ssadd (entlast) currobj))
(setq coords (list 
(list 1919.4375 820.117) 
(list 1845.415 820.667) 
(list 1845.415 820.49) 
(list 1919.4375 820.04)))
(apply 'command (append '("pline") coords '("c")))
(setq currobj (ssadd (entlast) currobj))
(setq coords (list 
(list 1919.4375 819.897) 
(list 1845.415 820.347) 
(list 1845.415 820.17) 
(list 1919.4375 819.82)))
(apply 'command (append '("pline") coords '("c")))
(setq currobj (ssadd (entlast) currobj))
(setq coords (list 
(list 1919.4375 819.677) 
(list 1845.415 820.027) 
(list 1845.415 819.85) 
(list 1919.4375 819.6)))
(apply 'command (append '("pline") coords '("c")))
(setq currobj (ssadd (entlast) currobj))
(setq coords (list 
(list 1919.4375 819.457) 
(list 1845.415 819.707) 
(list 1845.415 819.53) 
(list 1919.4375 819.38)))
(apply 'command (append '("pline") coords '("c")))
(setq currobj (ssadd (entlast) currobj))
(setq coords (list 
(list 1919.4375 819.237) 
(list 1845.415 819.387) 
(list 1845.415 819.21) 
(list 1919.4375 819.16)))
(apply 'command (append '("pline") coords '("c")))
(setq currobj (ssadd (entlast) currobj))
(setq coords (list 
(list 1919.4375 819.017) 
(list 1845.415 819.067) 
(list 1845.415 818.89) 
(list 1919.4375 818.94)))
(apply 'command (append '("pline") coords '("c")))
(setq currobj (ssadd (entlast) currobj))
(setq coords (list 
(list 1919.4375 818.797) 
(list 1845.415 818.747) 
(list 1845.415 818.57) 
(list 1919.4375 818.72)))
(apply 'command (append '("pline") coords '("c")))
(setq currobj (ssadd (entlast) currobj))
(setq coords (list 
(list 1919.4375 818.577) 
(list 1845.415 818.427) 
(list 1845.415 818.25) 
(list 1919.4375 818.5)))
(apply 'command (append '("pline") coords '("c")))
(setq currobj (ssadd (entlast) currobj))
(setq coords (list 
(list 1919.4375 818.357) 
(list 1845.415 818.107) 
(list 1845.415 817.93) 
(list 1919.4375 818.28)))
(apply 'command (append '("pline") coords '("c")))
(setq currobj (ssadd (entlast) currobj))
(setq coords (list 
(list 1919.4375 818.137) 
(list 1845.415 817.787) 
(list 1845.415 817.61) 
(list 1919.4375 818.06)))
(apply 'command (append '("pline") coords '("c")))
(setq currobj (ssadd (entlast) currobj))
(setq coords (list 
(list 1919.4375 817.917) 
(list 1845.415 817.467) 
(list 1845.415 817.29) 
(list 1919.4375 817.84)))
(apply 'command (append '("pline") coords '("c")))
(setq currobj (ssadd (entlast) currobj))
(setq coords (list 
(list 1919.4375 817.697) 
(list 1845.415 817.147) 
(list 1845.415 816.97) 
(list 1919.4375 817.62)))
(apply 'command (append '("pline") coords '("c")))
(setq currobj (ssadd (entlast) currobj))
(setq coords (list 
(list 1919.4375 817.477) 
(list 1845.415 816.827) 
(list 1845.415 816.65) 
(list 1919.4375 817.4)))
(apply 'command (append '("pline") coords '("c")))
(setq currobj (ssadd (entlast) currobj))
(command "_layer" "set" "nitride" "")
(command "_layer" "set" "text" "")
(command "_circle" "1919.0625,806.257" "0.075")
(command "_circle" "1919.0625,806.557" "0.075")
(command "_circle" "1919.0625,806.857" "0.075")
(command "_circle" "1919.0625,807.157" "0.075")
(command "_circle" "1919.0625,807.457" "0.075")
(command "_circle" "1918.7625,806.257" "0.075")
(command "_circle" "1918.7625,806.557" "0.075")
(command "_circle" "1918.7625,806.857" "0.075")
(command "_circle" "1918.7625,807.157" "0.075")
(command "_circle" "1918.7625,807.457" "0.075")
(command "_circle" "1918.4625,806.257" "0.075")
(command "_circle" "1918.4625,806.557" "0.075")
(command "_circle" "1918.4625,806.857" "0.075")
(command "_circle" "1918.4625,807.157" "0.075")
(command "_circle" "1918.4625,807.457" "0.075")
(command "_circle" "1918.1625,806.257" "0.075")
(command "_circle" "1918.1625,806.557" "0.075")
(command "_circle" "1918.1625,806.857" "0.075")
(command "_circle" "1918.1625,807.157" "0.075")
(command "_circle" "1918.1625,807.457" "0.075")
(command "_circle" "1917.8625,806.257" "0.075")
(command "_circle" "1917.8625,806.557" "0.075")
(command "_circle" "1917.8625,806.857" "0.075")
(command "_circle" "1917.8625,807.157" "0.075")
(command "_circle" "1917.8625,807.457" "0.075")
(command "_layer" "set" "nitride" "")
(setq coords (list 
(list 1920.2625 831.7) 
(list 1920.2625 836.7) 
(list 1919.7375 836.7) 
(list 1919.7375 831.7)))
(apply 'command (append '("pline") coords '("c")))
(setq currobj (ssadd (entlast) currobj))
(command "_layer" "set" "prebias" "")
(command "_rectangle" "1919.7375,831.7" "1920.2625,836.7")
(setq currobj (ssadd (entlast) currobj))
(command "_layer" "set" "nitride" "")
(setq cooledsinglenanobeam6 currobj)
(setq currobj nil)
(setq currobj (ssadd))
; DRAWING PHOTONIC CRYSTAL
(command "_layer" "set" "negYjunc" "")
(setq coords (list 
(list 1920.125 866.7) 
(list 1920 851.7) 
(list 1920 866.7)))
(apply 'command (append '("pline") coords '("c")))
(setq currobj (ssadd (entlast) currobj))
(setq coords (list 
(list 1920.2625 836.7) 
(list 1920.405 866.7) 
(list 1921.102 866.7) 
(list 1921.102 836.7)))
(apply 'command (append '("pline") coords '("c")))
(setq currobj (ssadd (entlast) currobj))
(setq coords (list 
(list 1919.875 866.7) 
(list 1920 851.7) 
(list 1920 866.7)))
(apply 'command (append '("pline") coords '("c")))
(setq currobj (ssadd (entlast) currobj))
(setq coords (list 
(list 1919.7375 836.7) 
(list 1919.595 866.7) 
(list 1918.898 866.7) 
(list 1918.898 836.7)))
(apply 'command (append '("pline") coords '("c")))
(setq currobj (ssadd (entlast) currobj))
(command "_layer" "set" "nitride" "")
(setq yjunction6 currobj)
(setq currobj nil)
(setq currobj (ssadd))
(setq tap6 nil)
(setq tap6 (ssadd))
(command "_layer" "set" "phc" "")
(setq coords (list 
(list 1920 866.7) 
(list 1920.125 866.7) 
(list 1920.125 866.7103) 
(list 1920.125 866.7206) 
(list 1920.125 866.7308) 
(list 1920.125 866.7411) 
(list 1920.125 866.7514) 
(list 1920.125 866.7617) 
(list 1920.125 866.7719) 
(list 1920.125 866.7822) 
(list 1920.125 866.7925) 
(list 1920.125 866.8028) 
(list 1920.125 866.8131) 
(list 1920.125 866.8233) 
(list 1920.125 866.8336) 
(list 1920.125 866.8439) 
(list 1920.125 866.8542) 
(list 1920.125 866.8644) 
(list 1920.125 866.8747) 
(list 1920.125 866.885) 
(list 1920.125 866.8953) 
(list 1920.125 866.9056) 
(list 1920.125 866.9158) 
(list 1920.125 866.9261) 
(list 1920.125 866.9364) 
(list 1920.125 866.9467) 
(list 1920.125 866.9569) 
(list 1920.125 866.9672) 
(list 1920.125 866.9775) 
(list 1920.125 866.9878) 
(list 1920.125 866.9981) 
(list 1920.125 867.0083) 
(list 1920.125 867.0186) 
(list 1920.125 867.0289) 
(list 1920.125 867.0392) 
(list 1920.125 867.0494) 
(list 1920.125 867.0597) 
(list 1920.125 867.07) 
(list 1920 867.07)))
(apply 'command (append '("pline") coords '("c")))
(setq tap6 (ssadd (entlast) tap6))
(command "_mirror" (entlast) "" "1920,900" "1920,901" "No")
(setq tap6 (ssadd (entlast) tap6))
(setq coords (list 
(list 1920.4147 866.7) 
(list 1920.405 866.7) 
(list 1920.4053 866.7103) 
(list 1920.4055 866.7206) 
(list 1920.4057 866.7308) 
(list 1920.4059 866.7411) 
(list 1920.4059 866.7514) 
(list 1920.4059 866.7617) 
(list 1920.4058 866.7719) 
(list 1920.4055 866.7822) 
(list 1920.4052 866.7925) 
(list 1920.4048 866.8028) 
(list 1920.4044 866.8131) 
(list 1920.4038 866.8233) 
(list 1920.4033 866.8336) 
(list 1920.4027 866.8439) 
(list 1920.4022 866.8542) 
(list 1920.4017 866.8644) 
(list 1920.4013 866.8747) 
(list 1920.4011 866.885) 
(list 1920.4009 866.8953) 
(list 1920.4009 866.9056) 
(list 1920.4011 866.9158) 
(list 1920.4015 866.9261) 
(list 1920.402 866.9364) 
(list 1920.4027 866.9467) 
(list 1920.4036 866.9569) 
(list 1920.4046 866.9672) 
(list 1920.4057 866.9775) 
(list 1920.4069 866.9878) 
(list 1920.4082 866.9981) 
(list 1920.4094 867.0083) 
(list 1920.4107 867.0186) 
(list 1920.4118 867.0289) 
(list 1920.4128 867.0392) 
(list 1920.4137 867.0494) 
(list 1920.4143 867.0597) 
(list 1920.4147 867.07) 
(list 1920.4147 867.07)))
(apply 'command (append '("pline") coords '("c")))
(setq tap6 (ssadd (entlast) tap6))
(command "_mirror" (entlast) "" "1920,900" "1920,901" "No")
(setq tap6 (ssadd (entlast) tap6))
(setq coords (list 
(list 1921.102 866.7) 
(list 1920.4147 866.7) 
(list 1920.4147 866.7103) 
(list 1920.4147 866.7206) 
(list 1920.4147 866.7308) 
(list 1920.4147 866.7411) 
(list 1920.4147 866.7514) 
(list 1920.4147 866.7617) 
(list 1920.4147 866.7719) 
(list 1920.4147 866.7822) 
(list 1920.4147 866.7925) 
(list 1920.4147 866.8028) 
(list 1920.4147 866.8131) 
(list 1920.4147 866.8233) 
(list 1920.4147 866.8336) 
(list 1920.4147 866.8439) 
(list 1920.4147 866.8542) 
(list 1920.4147 866.8644) 
(list 1920.4147 866.8747) 
(list 1920.4147 866.885) 
(list 1920.4147 866.8953) 
(list 1920.4147 866.9056) 
(list 1920.4147 866.9158) 
(list 1920.4147 866.9261) 
(list 1920.4147 866.9364) 
(list 1920.4147 866.9467) 
(list 1920.4147 866.9569) 
(list 1920.4147 866.9672) 
(list 1920.4147 866.9775) 
(list 1920.4147 866.9878) 
(list 1920.4147 866.9981) 
(list 1920.4147 867.0083) 
(list 1920.4147 867.0186) 
(list 1920.4147 867.0289) 
(list 1920.4147 867.0392) 
(list 1920.4147 867.0494) 
(list 1920.4147 867.0597) 
(list 1920.4147 867.07) 
(list 1921.102 867.07)))
(apply 'command (append '("pline") coords '("c")))
(setq tap6 (ssadd (entlast) tap6))
(command "_mirror" (entlast) "" "1920,900" "1920,901" "No")
(setq tap6 (ssadd (entlast) tap6))
(setq coords (list 
(list 1920 867.07) 
(list 1920.125 867.07) 
(list 1920.125 867.0803) 
(list 1920.125 867.0906) 
(list 1920.125 867.1008) 
(list 1920.125 867.1111) 
(list 1920.125 867.1214) 
(list 1920.125 867.1317) 
(list 1920.125 867.1419) 
(list 1920.125 867.1522) 
(list 1920.125 867.1625) 
(list 1920.125 867.1728) 
(list 1920.125 867.1831) 
(list 1920.125 867.1933) 
(list 1920.125 867.2036) 
(list 1920.125 867.2139) 
(list 1920.125 867.2242) 
(list 1920.125 867.2344) 
(list 1920.125 867.2447) 
(list 1920.125 867.255) 
(list 1920.125 867.2653) 
(list 1920.125 867.2756) 
(list 1920.125 867.2858) 
(list 1920.125 867.2961) 
(list 1920.125 867.3064) 
(list 1920.125 867.3167) 
(list 1920.125 867.3269) 
(list 1920.125 867.3372) 
(list 1920.125 867.3475) 
(list 1920.125 867.3578) 
(list 1920.125 867.3681) 
(list 1920.125 867.3783) 
(list 1920.125 867.3886) 
(list 1920.125 867.3989) 
(list 1920.125 867.4092) 
(list 1920.125 867.4194) 
(list 1920.125 867.4297) 
(list 1920.125 867.44) 
(list 1920 867.44)))
(apply 'command (append '("pline") coords '("c")))
(setq tap6 (ssadd (entlast) tap6))
(command "_mirror" (entlast) "" "1920,900" "1920,901" "No")
(setq tap6 (ssadd (entlast) tap6))
(setq coords (list 
(list 1920.4245 867.07) 
(list 1920.4147 867.07) 
(list 1920.4149 867.0803) 
(list 1920.4147 867.0906) 
(list 1920.4143 867.1008) 
(list 1920.4135 867.1111) 
(list 1920.4125 867.1214) 
(list 1920.4112 867.1317) 
(list 1920.4097 867.1419) 
(list 1920.408 867.1522) 
(list 1920.4062 867.1625) 
(list 1920.4042 867.1728) 
(list 1920.4023 867.1831) 
(list 1920.4004 867.1933) 
(list 1920.3986 867.2036) 
(list 1920.3969 867.2139) 
(list 1920.3955 867.2242) 
(list 1920.3944 867.2344) 
(list 1920.3936 867.2447) 
(list 1920.3932 867.255) 
(list 1920.3932 867.2653) 
(list 1920.3936 867.2756) 
(list 1920.3944 867.2858) 
(list 1920.3956 867.2961) 
(list 1920.3973 867.3064) 
(list 1920.3992 867.3167) 
(list 1920.4015 867.3269) 
(list 1920.404 867.3372) 
(list 1920.4066 867.3475) 
(list 1920.4094 867.3578) 
(list 1920.4121 867.3681) 
(list 1920.4148 867.3783) 
(list 1920.4173 867.3886) 
(list 1920.4195 867.3989) 
(list 1920.4214 867.4092) 
(list 1920.4229 867.4194) 
(list 1920.4239 867.4297) 
(list 1920.4245 867.44) 
(list 1920.4245 867.44)))
(apply 'command (append '("pline") coords '("c")))
(setq tap6 (ssadd (entlast) tap6))
(command "_mirror" (entlast) "" "1920,900" "1920,901" "No")
(setq tap6 (ssadd (entlast) tap6))
(setq coords (list 
(list 1921.102 867.07) 
(list 1920.4245 867.07) 
(list 1920.4245 867.0803) 
(list 1920.4245 867.0906) 
(list 1920.4245 867.1008) 
(list 1920.4245 867.1111) 
(list 1920.4245 867.1214) 
(list 1920.4245 867.1317) 
(list 1920.4245 867.1419) 
(list 1920.4245 867.1522) 
(list 1920.4245 867.1625) 
(list 1920.4245 867.1728) 
(list 1920.4245 867.1831) 
(list 1920.4245 867.1933) 
(list 1920.4245 867.2036) 
(list 1920.4245 867.2139) 
(list 1920.4245 867.2242) 
(list 1920.4245 867.2344) 
(list 1920.4245 867.2447) 
(list 1920.4245 867.255) 
(list 1920.4245 867.2653) 
(list 1920.4245 867.2756) 
(list 1920.4245 867.2858) 
(list 1920.4245 867.2961) 
(list 1920.4245 867.3064) 
(list 1920.4245 867.3167) 
(list 1920.4245 867.3269) 
(list 1920.4245 867.3372) 
(list 1920.4245 867.3475) 
(list 1920.4245 867.3578) 
(list 1920.4245 867.3681) 
(list 1920.4245 867.3783) 
(list 1920.4245 867.3886) 
(list 1920.4245 867.3989) 
(list 1920.4245 867.4092) 
(list 1920.4245 867.4194) 
(list 1920.4245 867.4297) 
(list 1920.4245 867.44) 
(list 1921.102 867.44)))
(apply 'command (append '("pline") coords '("c")))
(setq tap6 (ssadd (entlast) tap6))
(command "_mirror" (entlast) "" "1920,900" "1920,901" "No")
(setq tap6 (ssadd (entlast) tap6))
(setq coords (list 
(list 1920 867.44) 
(list 1920.125 867.44) 
(list 1920.125 867.4503) 
(list 1920.125 867.4606) 
(list 1920.125 867.4708) 
(list 1920.125 867.4811) 
(list 1920.125 867.4914) 
(list 1920.125 867.5017) 
(list 1920.125 867.5119) 
(list 1920.125 867.5222) 
(list 1920.125 867.5325) 
(list 1920.125 867.5428) 
(list 1920.125 867.5531) 
(list 1920.125 867.5633) 
(list 1920.125 867.5736) 
(list 1920.125 867.5839) 
(list 1920.125 867.5942) 
(list 1920.125 867.6044) 
(list 1920.125 867.6147) 
(list 1920.125 867.625) 
(list 1920.125 867.6353) 
(list 1920.125 867.6456) 
(list 1920.125 867.6558) 
(list 1920.125 867.6661) 
(list 1920.125 867.6764) 
(list 1920.125 867.6867) 
(list 1920.125 867.6969) 
(list 1920.125 867.7072) 
(list 1920.125 867.7175) 
(list 1920.125 867.7278) 
(list 1920.125 867.7381) 
(list 1920.125 867.7483) 
(list 1920.125 867.7586) 
(list 1920.125 867.7689) 
(list 1920.125 867.7792) 
(list 1920.125 867.7894) 
(list 1920.125 867.7997) 
(list 1920.125 867.81) 
(list 1920 867.81)))
(apply 'command (append '("pline") coords '("c")))
(setq tap6 (ssadd (entlast) tap6))
(command "_mirror" (entlast) "" "1920,900" "1920,901" "No")
(setq tap6 (ssadd (entlast) tap6))
(setq coords (list 
(list 1920.4342 867.44) 
(list 1920.4245 867.44) 
(list 1920.4245 867.4503) 
(list 1920.4239 867.4606) 
(list 1920.4228 867.4708) 
(list 1920.4212 867.4811) 
(list 1920.4191 867.4914) 
(list 1920.4166 867.5017) 
(list 1920.4137 867.5119) 
(list 1920.4105 867.5222) 
(list 1920.4071 867.5325) 
(list 1920.4036 867.5428) 
(list 1920.4002 867.5531) 
(list 1920.3969 867.5633) 
(list 1920.3938 867.5736) 
(list 1920.3911 867.5839) 
(list 1920.3888 867.5942) 
(list 1920.3871 867.6044) 
(list 1920.3859 867.6147) 
(list 1920.3853 867.625) 
(list 1920.3855 867.6353) 
(list 1920.3863 867.6456) 
(list 1920.3877 867.6558) 
(list 1920.3898 867.6661) 
(list 1920.3925 867.6764) 
(list 1920.3958 867.6867) 
(list 1920.3994 867.6969) 
(list 1920.4034 867.7072) 
(list 1920.4076 867.7175) 
(list 1920.4118 867.7278) 
(list 1920.4161 867.7381) 
(list 1920.4201 867.7483) 
(list 1920.4239 867.7586) 
(list 1920.4272 867.7689) 
(list 1920.4299 867.7792) 
(list 1920.4321 867.7894) 
(list 1920.4335 867.7997) 
(list 1920.4342 867.81) 
(list 1920.4342 867.81)))
(apply 'command (append '("pline") coords '("c")))
(setq tap6 (ssadd (entlast) tap6))
(command "_mirror" (entlast) "" "1920,900" "1920,901" "No")
(setq tap6 (ssadd (entlast) tap6))
(setq coords (list 
(list 1921.102 867.44) 
(list 1920.4342 867.44) 
(list 1920.4342 867.4503) 
(list 1920.4342 867.4606) 
(list 1920.4342 867.4708) 
(list 1920.4342 867.4811) 
(list 1920.4342 867.4914) 
(list 1920.4342 867.5017) 
(list 1920.4342 867.5119) 
(list 1920.4342 867.5222) 
(list 1920.4342 867.5325) 
(list 1920.4342 867.5428) 
(list 1920.4342 867.5531) 
(list 1920.4342 867.5633) 
(list 1920.4342 867.5736) 
(list 1920.4342 867.5839) 
(list 1920.4342 867.5942) 
(list 1920.4342 867.6044) 
(list 1920.4342 867.6147) 
(list 1920.4342 867.625) 
(list 1920.4342 867.6353) 
(list 1920.4342 867.6456) 
(list 1920.4342 867.6558) 
(list 1920.4342 867.6661) 
(list 1920.4342 867.6764) 
(list 1920.4342 867.6867) 
(list 1920.4342 867.6969) 
(list 1920.4342 867.7072) 
(list 1920.4342 867.7175) 
(list 1920.4342 867.7278) 
(list 1920.4342 867.7381) 
(list 1920.4342 867.7483) 
(list 1920.4342 867.7586) 
(list 1920.4342 867.7689) 
(list 1920.4342 867.7792) 
(list 1920.4342 867.7894) 
(list 1920.4342 867.7997) 
(list 1920.4342 867.81) 
(list 1921.102 867.81)))
(apply 'command (append '("pline") coords '("c")))
(setq tap6 (ssadd (entlast) tap6))
(command "_mirror" (entlast) "" "1920,900" "1920,901" "No")
(setq tap6 (ssadd (entlast) tap6))
(setq coords (list 
(list 1920 867.81) 
(list 1920.125 867.81) 
(list 1920.125 867.8203) 
(list 1920.125 867.8306) 
(list 1920.125 867.8408) 
(list 1920.125 867.8511) 
(list 1920.125 867.8614) 
(list 1920.125 867.8717) 
(list 1920.125 867.8819) 
(list 1920.125 867.8922) 
(list 1920.125 867.9025) 
(list 1920.125 867.9128) 
(list 1920.125 867.9231) 
(list 1920.125 867.9333) 
(list 1920.125 867.9436) 
(list 1920.125 867.9539) 
(list 1920.125 867.9642) 
(list 1920.125 867.9744) 
(list 1920.125 867.9847) 
(list 1920.125 867.995) 
(list 1920.125 868.0053) 
(list 1920.125 868.0156) 
(list 1920.125 868.0258) 
(list 1920.125 868.0361) 
(list 1920.125 868.0464) 
(list 1920.125 868.0567) 
(list 1920.125 868.0669) 
(list 1920.125 868.0772) 
(list 1920.125 868.0875) 
(list 1920.125 868.0978) 
(list 1920.125 868.1081) 
(list 1920.125 868.1183) 
(list 1920.125 868.1286) 
(list 1920.125 868.1389) 
(list 1920.125 868.1492) 
(list 1920.125 868.1594) 
(list 1920.125 868.1697) 
(list 1920.125 868.18) 
(list 1920 868.18)))
(apply 'command (append '("pline") coords '("c")))
(setq tap6 (ssadd (entlast) tap6))
(command "_mirror" (entlast) "" "1920,900" "1920,901" "No")
(setq tap6 (ssadd (entlast) tap6))
(setq coords (list 
(list 1920.4439 867.81) 
(list 1920.4342 867.81) 
(list 1920.4341 867.8203) 
(list 1920.4331 867.8306) 
(list 1920.4314 867.8408) 
(list 1920.4289 867.8511) 
(list 1920.4257 867.8614) 
(list 1920.4219 867.8717) 
(list 1920.4176 867.8819) 
(list 1920.4129 867.8922) 
(list 1920.408 867.9025) 
(list 1920.403 867.9128) 
(list 1920.3981 867.9231) 
(list 1920.3934 867.9333) 
(list 1920.3891 867.9436) 
(list 1920.3853 867.9539) 
(list 1920.3821 867.9642) 
(list 1920.3797 867.9744) 
(list 1920.3781 867.9847) 
(list 1920.3775 867.995) 
(list 1920.3777 868.0053) 
(list 1920.3789 868.0156) 
(list 1920.381 868.0258) 
(list 1920.384 868.0361) 
(list 1920.3878 868.0464) 
(list 1920.3923 868.0567) 
(list 1920.3973 868.0669) 
(list 1920.4028 868.0772) 
(list 1920.4085 868.0875) 
(list 1920.4143 868.0978) 
(list 1920.42 868.1081) 
(list 1920.4254 868.1183) 
(list 1920.4304 868.1286) 
(list 1920.4348 868.1389) 
(list 1920.4385 868.1492) 
(list 1920.4413 868.1594) 
(list 1920.4431 868.1697) 
(list 1920.4439 868.18) 
(list 1920.4439 868.18)))
(apply 'command (append '("pline") coords '("c")))
(setq tap6 (ssadd (entlast) tap6))
(command "_mirror" (entlast) "" "1920,900" "1920,901" "No")
(setq tap6 (ssadd (entlast) tap6))
(setq coords (list 
(list 1921.102 867.81) 
(list 1920.4439 867.81) 
(list 1920.4439 867.8203) 
(list 1920.4439 867.8306) 
(list 1920.4439 867.8408) 
(list 1920.4439 867.8511) 
(list 1920.4439 867.8614) 
(list 1920.4439 867.8717) 
(list 1920.4439 867.8819) 
(list 1920.4439 867.8922) 
(list 1920.4439 867.9025) 
(list 1920.4439 867.9128) 
(list 1920.4439 867.9231) 
(list 1920.4439 867.9333) 
(list 1920.4439 867.9436) 
(list 1920.4439 867.9539) 
(list 1920.4439 867.9642) 
(list 1920.4439 867.9744) 
(list 1920.4439 867.9847) 
(list 1920.4439 867.995) 
(list 1920.4439 868.0053) 
(list 1920.4439 868.0156) 
(list 1920.4439 868.0258) 
(list 1920.4439 868.0361) 
(list 1920.4439 868.0464) 
(list 1920.4439 868.0567) 
(list 1920.4439 868.0669) 
(list 1920.4439 868.0772) 
(list 1920.4439 868.0875) 
(list 1920.4439 868.0978) 
(list 1920.4439 868.1081) 
(list 1920.4439 868.1183) 
(list 1920.4439 868.1286) 
(list 1920.4439 868.1389) 
(list 1920.4439 868.1492) 
(list 1920.4439 868.1594) 
(list 1920.4439 868.1697) 
(list 1920.4439 868.18) 
(list 1921.102 868.18)))
(apply 'command (append '("pline") coords '("c")))
(setq tap6 (ssadd (entlast) tap6))
(command "_mirror" (entlast) "" "1920,900" "1920,901" "No")
(setq tap6 (ssadd (entlast) tap6))
(setq coords (list 
(list 1920 868.18) 
(list 1920.125 868.18) 
(list 1920.125 868.1903) 
(list 1920.125 868.2006) 
(list 1920.125 868.2108) 
(list 1920.125 868.2211) 
(list 1920.125 868.2314) 
(list 1920.125 868.2417) 
(list 1920.125 868.2519) 
(list 1920.125 868.2622) 
(list 1920.125 868.2725) 
(list 1920.125 868.2828) 
(list 1920.125 868.2931) 
(list 1920.125 868.3033) 
(list 1920.125 868.3136) 
(list 1920.125 868.3239) 
(list 1920.125 868.3342) 
(list 1920.125 868.3444) 
(list 1920.125 868.3547) 
(list 1920.125 868.365) 
(list 1920.125 868.3753) 
(list 1920.125 868.3856) 
(list 1920.125 868.3958) 
(list 1920.125 868.4061) 
(list 1920.125 868.4164) 
(list 1920.125 868.4267) 
(list 1920.125 868.4369) 
(list 1920.125 868.4472) 
(list 1920.125 868.4575) 
(list 1920.125 868.4678) 
(list 1920.125 868.4781) 
(list 1920.125 868.4883) 
(list 1920.125 868.4986) 
(list 1920.125 868.5089) 
(list 1920.125 868.5192) 
(list 1920.125 868.5294) 
(list 1920.125 868.5397) 
(list 1920.125 868.55) 
(list 1920 868.55)))
(apply 'command (append '("pline") coords '("c")))
(setq tap6 (ssadd (entlast) tap6))
(command "_mirror" (entlast) "" "1920,900" "1920,901" "No")
(setq tap6 (ssadd (entlast) tap6))
(setq coords (list 
(list 1920.4537 868.18) 
(list 1920.4439 868.18) 
(list 1920.4437 868.1903) 
(list 1920.4423 868.2006) 
(list 1920.4399 868.2108) 
(list 1920.4366 868.2211) 
(list 1920.4323 868.2314) 
(list 1920.4272 868.2417) 
(list 1920.4215 868.2519) 
(list 1920.4154 868.2622) 
(list 1920.409 868.2725) 
(list 1920.4025 868.2828) 
(list 1920.3961 868.2931) 
(list 1920.39 868.3033) 
(list 1920.3844 868.3136) 
(list 1920.3795 868.3239) 
(list 1920.3755 868.3342) 
(list 1920.3724 868.3444) 
(list 1920.3704 868.3547) 
(list 1920.3696 868.365) 
(list 1920.37 868.3753) 
(list 1920.3716 868.3856) 
(list 1920.3743 868.3958) 
(list 1920.3782 868.4061) 
(list 1920.3831 868.4164) 
(list 1920.3888 868.4267) 
(list 1920.3953 868.4369) 
(list 1920.4022 868.4472) 
(list 1920.4094 868.4575) 
(list 1920.4168 868.4678) 
(list 1920.4239 868.4781) 
(list 1920.4308 868.4883) 
(list 1920.437 868.4986) 
(list 1920.4425 868.5089) 
(list 1920.4471 868.5192) 
(list 1920.4505 868.5294) 
(list 1920.4527 868.5397) 
(list 1920.4537 868.55) 
(list 1920.4537 868.55)))
(apply 'command (append '("pline") coords '("c")))
(setq tap6 (ssadd (entlast) tap6))
(command "_mirror" (entlast) "" "1920,900" "1920,901" "No")
(setq tap6 (ssadd (entlast) tap6))
(setq coords (list 
(list 1921.102 868.18) 
(list 1920.4537 868.18) 
(list 1920.4537 868.1903) 
(list 1920.4537 868.2006) 
(list 1920.4537 868.2108) 
(list 1920.4537 868.2211) 
(list 1920.4537 868.2314) 
(list 1920.4537 868.2417) 
(list 1920.4537 868.2519) 
(list 1920.4537 868.2622) 
(list 1920.4537 868.2725) 
(list 1920.4537 868.2828) 
(list 1920.4537 868.2931) 
(list 1920.4537 868.3033) 
(list 1920.4537 868.3136) 
(list 1920.4537 868.3239) 
(list 1920.4537 868.3342) 
(list 1920.4537 868.3444) 
(list 1920.4537 868.3547) 
(list 1920.4537 868.365) 
(list 1920.4537 868.3753) 
(list 1920.4537 868.3856) 
(list 1920.4537 868.3958) 
(list 1920.4537 868.4061) 
(list 1920.4537 868.4164) 
(list 1920.4537 868.4267) 
(list 1920.4537 868.4369) 
(list 1920.4537 868.4472) 
(list 1920.4537 868.4575) 
(list 1920.4537 868.4678) 
(list 1920.4537 868.4781) 
(list 1920.4537 868.4883) 
(list 1920.4537 868.4986) 
(list 1920.4537 868.5089) 
(list 1920.4537 868.5192) 
(list 1920.4537 868.5294) 
(list 1920.4537 868.5397) 
(list 1920.4537 868.55) 
(list 1921.102 868.55)))
(apply 'command (append '("pline") coords '("c")))
(setq tap6 (ssadd (entlast) tap6))
(command "_mirror" (entlast) "" "1920,900" "1920,901" "No")
(setq tap6 (ssadd (entlast) tap6))
(setq coords (list 
(list 1920 868.55) 
(list 1920.125 868.55) 
(list 1920.125 868.5603) 
(list 1920.125 868.5706) 
(list 1920.125 868.5808) 
(list 1920.125 868.5911) 
(list 1920.125 868.6014) 
(list 1920.125 868.6117) 
(list 1920.125 868.6219) 
(list 1920.125 868.6322) 
(list 1920.125 868.6425) 
(list 1920.125 868.6528) 
(list 1920.125 868.6631) 
(list 1920.125 868.6733) 
(list 1920.125 868.6836) 
(list 1920.125 868.6939) 
(list 1920.125 868.7042) 
(list 1920.125 868.7144) 
(list 1920.125 868.7247) 
(list 1920.125 868.735) 
(list 1920.125 868.7453) 
(list 1920.125 868.7556) 
(list 1920.125 868.7658) 
(list 1920.125 868.7761) 
(list 1920.125 868.7864) 
(list 1920.125 868.7967) 
(list 1920.125 868.8069) 
(list 1920.125 868.8172) 
(list 1920.125 868.8275) 
(list 1920.125 868.8378) 
(list 1920.125 868.8481) 
(list 1920.125 868.8583) 
(list 1920.125 868.8686) 
(list 1920.125 868.8789) 
(list 1920.125 868.8892) 
(list 1920.125 868.8994) 
(list 1920.125 868.9097) 
(list 1920.125 868.92) 
(list 1920 868.92)))
(apply 'command (append '("pline") coords '("c")))
(setq tap6 (ssadd (entlast) tap6))
(command "_mirror" (entlast) "" "1920,900" "1920,901" "No")
(setq tap6 (ssadd (entlast) tap6))
(setq coords (list 
(list 1920.4634 868.55) 
(list 1920.4537 868.55) 
(list 1920.4533 868.5603) 
(list 1920.4515 868.5706) 
(list 1920.4485 868.5808) 
(list 1920.4442 868.5911) 
(list 1920.4389 868.6014) 
(list 1920.4326 868.6117) 
(list 1920.4255 868.6219) 
(list 1920.4179 868.6322) 
(list 1920.4099 868.6425) 
(list 1920.4019 868.6528) 
(list 1920.394 868.6631) 
(list 1920.3865 868.6733) 
(list 1920.3797 868.6836) 
(list 1920.3737 868.6939) 
(list 1920.3688 868.7042) 
(list 1920.3651 868.7144) 
(list 1920.3627 868.7247) 
(list 1920.3617 868.735) 
(list 1920.3623 868.7453) 
(list 1920.3642 868.7556) 
(list 1920.3677 868.7658) 
(list 1920.3724 868.7761) 
(list 1920.3784 868.7864) 
(list 1920.3854 868.7967) 
(list 1920.3932 868.8069) 
(list 1920.4016 868.8172) 
(list 1920.4104 868.8275) 
(list 1920.4192 868.8378) 
(list 1920.4279 868.8481) 
(list 1920.4361 868.8583) 
(list 1920.4436 868.8686) 
(list 1920.4502 868.8789) 
(list 1920.4556 868.8892) 
(list 1920.4597 868.8994) 
(list 1920.4623 868.9097) 
(list 1920.4634 868.92) 
(list 1920.4634 868.92)))
(apply 'command (append '("pline") coords '("c")))
(setq tap6 (ssadd (entlast) tap6))
(command "_mirror" (entlast) "" "1920,900" "1920,901" "No")
(setq tap6 (ssadd (entlast) tap6))
(setq coords (list 
(list 1921.102 868.55) 
(list 1920.4634 868.55) 
(list 1920.4634 868.5603) 
(list 1920.4634 868.5706) 
(list 1920.4634 868.5808) 
(list 1920.4634 868.5911) 
(list 1920.4634 868.6014) 
(list 1920.4634 868.6117) 
(list 1920.4634 868.6219) 
(list 1920.4634 868.6322) 
(list 1920.4634 868.6425) 
(list 1920.4634 868.6528) 
(list 1920.4634 868.6631) 
(list 1920.4634 868.6733) 
(list 1920.4634 868.6836) 
(list 1920.4634 868.6939) 
(list 1920.4634 868.7042) 
(list 1920.4634 868.7144) 
(list 1920.4634 868.7247) 
(list 1920.4634 868.735) 
(list 1920.4634 868.7453) 
(list 1920.4634 868.7556) 
(list 1920.4634 868.7658) 
(list 1920.4634 868.7761) 
(list 1920.4634 868.7864) 
(list 1920.4634 868.7967) 
(list 1920.4634 868.8069) 
(list 1920.4634 868.8172) 
(list 1920.4634 868.8275) 
(list 1920.4634 868.8378) 
(list 1920.4634 868.8481) 
(list 1920.4634 868.8583) 
(list 1920.4634 868.8686) 
(list 1920.4634 868.8789) 
(list 1920.4634 868.8892) 
(list 1920.4634 868.8994) 
(list 1920.4634 868.9097) 
(list 1920.4634 868.92) 
(list 1921.102 868.92)))
(apply 'command (append '("pline") coords '("c")))
(setq tap6 (ssadd (entlast) tap6))
(command "_mirror" (entlast) "" "1920,900" "1920,901" "No")
(setq tap6 (ssadd (entlast) tap6))
(setq coords (list 
(list 1920 868.92) 
(list 1920.125 868.92) 
(list 1920.125 868.9303) 
(list 1920.125 868.9406) 
(list 1920.125 868.9508) 
(list 1920.125 868.9611) 
(list 1920.125 868.9714) 
(list 1920.125 868.9817) 
(list 1920.125 868.9919) 
(list 1920.125 869.0022) 
(list 1920.125 869.0125) 
(list 1920.125 869.0228) 
(list 1920.125 869.0331) 
(list 1920.125 869.0433) 
(list 1920.125 869.0536) 
(list 1920.125 869.0639) 
(list 1920.125 869.0742) 
(list 1920.125 869.0844) 
(list 1920.125 869.0947) 
(list 1920.125 869.105) 
(list 1920.125 869.1153) 
(list 1920.125 869.1256) 
(list 1920.125 869.1358) 
(list 1920.125 869.1461) 
(list 1920.125 869.1564) 
(list 1920.125 869.1667) 
(list 1920.125 869.1769) 
(list 1920.125 869.1872) 
(list 1920.125 869.1975) 
(list 1920.125 869.2078) 
(list 1920.125 869.2181) 
(list 1920.125 869.2283) 
(list 1920.125 869.2386) 
(list 1920.125 869.2489) 
(list 1920.125 869.2592) 
(list 1920.125 869.2694) 
(list 1920.125 869.2797) 
(list 1920.125 869.29) 
(list 1920 869.29)))
(apply 'command (append '("pline") coords '("c")))
(setq tap6 (ssadd (entlast) tap6))
(command "_mirror" (entlast) "" "1920,900" "1920,901" "No")
(setq tap6 (ssadd (entlast) tap6))
(setq coords (list 
(list 1920.4731 868.92) 
(list 1920.4634 868.92) 
(list 1920.4629 868.9303) 
(list 1920.4607 868.9406) 
(list 1920.457 868.9508) 
(list 1920.4519 868.9611) 
(list 1920.4455 868.9714) 
(list 1920.4379 868.9817) 
(list 1920.4294 868.9919) 
(list 1920.4203 869.0022) 
(list 1920.4108 869.0125) 
(list 1920.4013 869.0228) 
(list 1920.3919 869.0331) 
(list 1920.383 869.0433) 
(list 1920.375 869.0536) 
(list 1920.3679 869.0639) 
(list 1920.3621 869.0742) 
(list 1920.3577 869.0844) 
(list 1920.3549 869.0947) 
(list 1920.3539 869.105) 
(list 1920.3545 869.1153) 
(list 1920.3569 869.1256) 
(list 1920.361 869.1358) 
(list 1920.3666 869.1461) 
(list 1920.3736 869.1564) 
(list 1920.3819 869.1667) 
(list 1920.3911 869.1769) 
(list 1920.401 869.1872) 
(list 1920.4113 869.1975) 
(list 1920.4217 869.2078) 
(list 1920.4318 869.2181) 
(list 1920.4414 869.2283) 
(list 1920.4502 869.2386) 
(list 1920.4579 869.2489) 
(list 1920.4642 869.2592) 
(list 1920.4689 869.2694) 
(list 1920.4719 869.2797) 
(list 1920.4731 869.29) 
(list 1920.4731 869.29)))
(apply 'command (append '("pline") coords '("c")))
(setq tap6 (ssadd (entlast) tap6))
(command "_mirror" (entlast) "" "1920,900" "1920,901" "No")
(setq tap6 (ssadd (entlast) tap6))
(setq coords (list 
(list 1921.102 868.92) 
(list 1920.4731 868.92) 
(list 1920.4731 868.9303) 
(list 1920.4731 868.9406) 
(list 1920.4731 868.9508) 
(list 1920.4731 868.9611) 
(list 1920.4731 868.9714) 
(list 1920.4731 868.9817) 
(list 1920.4731 868.9919) 
(list 1920.4731 869.0022) 
(list 1920.4731 869.0125) 
(list 1920.4731 869.0228) 
(list 1920.4731 869.0331) 
(list 1920.4731 869.0433) 
(list 1920.4731 869.0536) 
(list 1920.4731 869.0639) 
(list 1920.4731 869.0742) 
(list 1920.4731 869.0844) 
(list 1920.4731 869.0947) 
(list 1920.4731 869.105) 
(list 1920.4731 869.1153) 
(list 1920.4731 869.1256) 
(list 1920.4731 869.1358) 
(list 1920.4731 869.1461) 
(list 1920.4731 869.1564) 
(list 1920.4731 869.1667) 
(list 1920.4731 869.1769) 
(list 1920.4731 869.1872) 
(list 1920.4731 869.1975) 
(list 1920.4731 869.2078) 
(list 1920.4731 869.2181) 
(list 1920.4731 869.2283) 
(list 1920.4731 869.2386) 
(list 1920.4731 869.2489) 
(list 1920.4731 869.2592) 
(list 1920.4731 869.2694) 
(list 1920.4731 869.2797) 
(list 1920.4731 869.29) 
(list 1921.102 869.29)))
(apply 'command (append '("pline") coords '("c")))
(setq tap6 (ssadd (entlast) tap6))
(command "_mirror" (entlast) "" "1920,900" "1920,901" "No")
(setq tap6 (ssadd (entlast) tap6))
(setq coords (list 
(list 1920 869.29) 
(list 1920.125 869.29) 
(list 1920.125 869.3003) 
(list 1920.125 869.3106) 
(list 1920.125 869.3208) 
(list 1920.125 869.3311) 
(list 1920.125 869.3414) 
(list 1920.125 869.3517) 
(list 1920.125 869.3619) 
(list 1920.125 869.3722) 
(list 1920.125 869.3825) 
(list 1920.125 869.3928) 
(list 1920.125 869.4031) 
(list 1920.125 869.4133) 
(list 1920.125 869.4236) 
(list 1920.125 869.4339) 
(list 1920.125 869.4442) 
(list 1920.125 869.4544) 
(list 1920.125 869.4647) 
(list 1920.125 869.475) 
(list 1920.125 869.4853) 
(list 1920.125 869.4956) 
(list 1920.125 869.5058) 
(list 1920.125 869.5161) 
(list 1920.125 869.5264) 
(list 1920.125 869.5367) 
(list 1920.125 869.5469) 
(list 1920.125 869.5572) 
(list 1920.125 869.5675) 
(list 1920.125 869.5778) 
(list 1920.125 869.5881) 
(list 1920.125 869.5983) 
(list 1920.125 869.6086) 
(list 1920.125 869.6189) 
(list 1920.125 869.6292) 
(list 1920.125 869.6394) 
(list 1920.125 869.6497) 
(list 1920.125 869.66) 
(list 1920 869.66)))
(apply 'command (append '("pline") coords '("c")))
(setq tap6 (ssadd (entlast) tap6))
(command "_mirror" (entlast) "" "1920,900" "1920,901" "No")
(setq tap6 (ssadd (entlast) tap6))
(setq coords (list 
(list 1920.4829 869.29) 
(list 1920.4731 869.29) 
(list 1920.4725 869.3003) 
(list 1920.4699 869.3106) 
(list 1920.4656 869.3208) 
(list 1920.4596 869.3311) 
(list 1920.452 869.3414) 
(list 1920.4432 869.3517) 
(list 1920.4334 869.3619) 
(list 1920.4228 869.3722) 
(list 1920.4118 869.3825) 
(list 1920.4007 869.3928) 
(list 1920.3898 869.4031) 
(list 1920.3796 869.4133) 
(list 1920.3702 869.4236) 
(list 1920.3621 869.4339) 
(list 1920.3554 869.4442) 
(list 1920.3504 869.4544) 
(list 1920.3472 869.4647) 
(list 1920.346 869.475) 
(list 1920.3468 869.4853) 
(list 1920.3496 869.4956) 
(list 1920.3543 869.5058) 
(list 1920.3608 869.5161) 
(list 1920.3689 869.5264) 
(list 1920.3784 869.5367) 
(list 1920.389 869.5469) 
(list 1920.4004 869.5572) 
(list 1920.4122 869.5675) 
(list 1920.4241 869.5778) 
(list 1920.4358 869.5881) 
(list 1920.4468 869.5983) 
(list 1920.4568 869.6086) 
(list 1920.4655 869.6189) 
(list 1920.4727 869.6292) 
(list 1920.4781 869.6394) 
(list 1920.4815 869.6497) 
(list 1920.4829 869.66) 
(list 1920.4829 869.66)))
(apply 'command (append '("pline") coords '("c")))
(setq tap6 (ssadd (entlast) tap6))
(command "_mirror" (entlast) "" "1920,900" "1920,901" "No")
(setq tap6 (ssadd (entlast) tap6))
(setq coords (list 
(list 1921.102 869.29) 
(list 1920.4829 869.29) 
(list 1920.4829 869.3003) 
(list 1920.4829 869.3106) 
(list 1920.4829 869.3208) 
(list 1920.4829 869.3311) 
(list 1920.4829 869.3414) 
(list 1920.4829 869.3517) 
(list 1920.4829 869.3619) 
(list 1920.4829 869.3722) 
(list 1920.4829 869.3825) 
(list 1920.4829 869.3928) 
(list 1920.4829 869.4031) 
(list 1920.4829 869.4133) 
(list 1920.4829 869.4236) 
(list 1920.4829 869.4339) 
(list 1920.4829 869.4442) 
(list 1920.4829 869.4544) 
(list 1920.4829 869.4647) 
(list 1920.4829 869.475) 
(list 1920.4829 869.4853) 
(list 1920.4829 869.4956) 
(list 1920.4829 869.5058) 
(list 1920.4829 869.5161) 
(list 1920.4829 869.5264) 
(list 1920.4829 869.5367) 
(list 1920.4829 869.5469) 
(list 1920.4829 869.5572) 
(list 1920.4829 869.5675) 
(list 1920.4829 869.5778) 
(list 1920.4829 869.5881) 
(list 1920.4829 869.5983) 
(list 1920.4829 869.6086) 
(list 1920.4829 869.6189) 
(list 1920.4829 869.6292) 
(list 1920.4829 869.6394) 
(list 1920.4829 869.6497) 
(list 1920.4829 869.66) 
(list 1921.102 869.66)))
(apply 'command (append '("pline") coords '("c")))
(setq tap6 (ssadd (entlast) tap6))
(command "_mirror" (entlast) "" "1920,900" "1920,901" "No")
(setq tap6 (ssadd (entlast) tap6))
(setq coords (list 
(list 1920 869.66) 
(list 1920.125 869.66) 
(list 1920.125 869.6703) 
(list 1920.125 869.6806) 
(list 1920.125 869.6908) 
(list 1920.125 869.7011) 
(list 1920.125 869.7114) 
(list 1920.125 869.7217) 
(list 1920.125 869.7319) 
(list 1920.125 869.7422) 
(list 1920.125 869.7525) 
(list 1920.125 869.7628) 
(list 1920.125 869.7731) 
(list 1920.125 869.7833) 
(list 1920.125 869.7936) 
(list 1920.125 869.8039) 
(list 1920.125 869.8142) 
(list 1920.125 869.8244) 
(list 1920.125 869.8347) 
(list 1920.125 869.845) 
(list 1920.125 869.8553) 
(list 1920.125 869.8656) 
(list 1920.125 869.8758) 
(list 1920.125 869.8861) 
(list 1920.125 869.8964) 
(list 1920.125 869.9067) 
(list 1920.125 869.9169) 
(list 1920.125 869.9272) 
(list 1920.125 869.9375) 
(list 1920.125 869.9478) 
(list 1920.125 869.9581) 
(list 1920.125 869.9683) 
(list 1920.125 869.9786) 
(list 1920.125 869.9889) 
(list 1920.125 869.9992) 
(list 1920.125 870.0094) 
(list 1920.125 870.0197) 
(list 1920.125 870.03) 
(list 1920 870.03)))
(apply 'command (append '("pline") coords '("c")))
(setq tap6 (ssadd (entlast) tap6))
(command "_mirror" (entlast) "" "1920,900" "1920,901" "No")
(setq tap6 (ssadd (entlast) tap6))
(setq coords (list 
(list 1920.4926 869.66) 
(list 1920.4829 869.66) 
(list 1920.4821 869.6703) 
(list 1920.4791 869.6806) 
(list 1920.4741 869.6908) 
(list 1920.4672 869.7011) 
(list 1920.4586 869.7114) 
(list 1920.4486 869.7217) 
(list 1920.4373 869.7319) 
(list 1920.4252 869.7422) 
(list 1920.4127 869.7525) 
(list 1920.4001 869.7628) 
(list 1920.3878 869.7731) 
(list 1920.3761 869.7833) 
(list 1920.3655 869.7936) 
(list 1920.3563 869.8039) 
(list 1920.3487 869.8142) 
(list 1920.3431 869.8244) 
(list 1920.3395 869.8347) 
(list 1920.3381 869.845) 
(list 1920.3391 869.8553) 
(list 1920.3422 869.8656) 
(list 1920.3476 869.8758) 
(list 1920.355 869.8861) 
(list 1920.3642 869.8964) 
(list 1920.375 869.9067) 
(list 1920.3869 869.9169) 
(list 1920.3998 869.9272) 
(list 1920.4132 869.9375) 
(list 1920.4266 869.9478) 
(list 1920.4397 869.9581) 
(list 1920.4521 869.9683) 
(list 1920.4634 869.9786) 
(list 1920.4732 869.9889) 
(list 1920.4813 869.9992) 
(list 1920.4873 870.0094) 
(list 1920.4911 870.0197) 
(list 1920.4926 870.03) 
(list 1920.4926 870.03)))
(apply 'command (append '("pline") coords '("c")))
(setq tap6 (ssadd (entlast) tap6))
(command "_mirror" (entlast) "" "1920,900" "1920,901" "No")
(setq tap6 (ssadd (entlast) tap6))
(setq coords (list 
(list 1921.102 869.66) 
(list 1920.4926 869.66) 
(list 1920.4926 869.6703) 
(list 1920.4926 869.6806) 
(list 1920.4926 869.6908) 
(list 1920.4926 869.7011) 
(list 1920.4926 869.7114) 
(list 1920.4926 869.7217) 
(list 1920.4926 869.7319) 
(list 1920.4926 869.7422) 
(list 1920.4926 869.7525) 
(list 1920.4926 869.7628) 
(list 1920.4926 869.7731) 
(list 1920.4926 869.7833) 
(list 1920.4926 869.7936) 
(list 1920.4926 869.8039) 
(list 1920.4926 869.8142) 
(list 1920.4926 869.8244) 
(list 1920.4926 869.8347) 
(list 1920.4926 869.845) 
(list 1920.4926 869.8553) 
(list 1920.4926 869.8656) 
(list 1920.4926 869.8758) 
(list 1920.4926 869.8861) 
(list 1920.4926 869.8964) 
(list 1920.4926 869.9067) 
(list 1920.4926 869.9169) 
(list 1920.4926 869.9272) 
(list 1920.4926 869.9375) 
(list 1920.4926 869.9478) 
(list 1920.4926 869.9581) 
(list 1920.4926 869.9683) 
(list 1920.4926 869.9786) 
(list 1920.4926 869.9889) 
(list 1920.4926 869.9992) 
(list 1920.4926 870.0094) 
(list 1920.4926 870.0197) 
(list 1920.4926 870.03) 
(list 1921.102 870.03)))
(apply 'command (append '("pline") coords '("c")))
(setq tap6 (ssadd (entlast) tap6))
(command "_mirror" (entlast) "" "1920,900" "1920,901" "No")
(setq tap6 (ssadd (entlast) tap6))
(setq coords (list 
(list 1920 870.03) 
(list 1920.125 870.03) 
(list 1920.125 870.0403) 
(list 1920.125 870.0506) 
(list 1920.125 870.0608) 
(list 1920.125 870.0711) 
(list 1920.125 870.0814) 
(list 1920.125 870.0917) 
(list 1920.125 870.1019) 
(list 1920.125 870.1122) 
(list 1920.125 870.1225) 
(list 1920.125 870.1328) 
(list 1920.125 870.1431) 
(list 1920.125 870.1533) 
(list 1920.125 870.1636) 
(list 1920.125 870.1739) 
(list 1920.125 870.1842) 
(list 1920.125 870.1944) 
(list 1920.125 870.2047) 
(list 1920.125 870.215) 
(list 1920.125 870.2253) 
(list 1920.125 870.2356) 
(list 1920.125 870.2458) 
(list 1920.125 870.2561) 
(list 1920.125 870.2664) 
(list 1920.125 870.2767) 
(list 1920.125 870.2869) 
(list 1920.125 870.2972) 
(list 1920.125 870.3075) 
(list 1920.125 870.3178) 
(list 1920.125 870.3281) 
(list 1920.125 870.3383) 
(list 1920.125 870.3486) 
(list 1920.125 870.3589) 
(list 1920.125 870.3692) 
(list 1920.125 870.3794) 
(list 1920.125 870.3897) 
(list 1920.125 870.4) 
(list 1920 870.4)))
(apply 'command (append '("pline") coords '("c")))
(setq tap6 (ssadd (entlast) tap6))
(command "_mirror" (entlast) "" "1920,900" "1920,901" "No")
(setq tap6 (ssadd (entlast) tap6))
(setq coords (list 
(list 1920.5023 870.03) 
(list 1920.4926 870.03) 
(list 1920.4917 870.0403) 
(list 1920.4883 870.0506) 
(list 1920.4827 870.0608) 
(list 1920.4749 870.0711) 
(list 1920.4652 870.0814) 
(list 1920.4539 870.0917) 
(list 1920.4413 870.1019) 
(list 1920.4277 870.1122) 
(list 1920.4136 870.1225) 
(list 1920.3995 870.1328) 
(list 1920.3857 870.1431) 
(list 1920.3726 870.1533) 
(list 1920.3608 870.1636) 
(list 1920.3505 870.1739) 
(list 1920.342 870.1842) 
(list 1920.3357 870.1944) 
(list 1920.3318 870.2047) 
(list 1920.3303 870.215) 
(list 1920.3313 870.2253) 
(list 1920.3349 870.2356) 
(list 1920.3409 870.2458) 
(list 1920.3492 870.2561) 
(list 1920.3595 870.2664) 
(list 1920.3715 870.2767) 
(list 1920.3849 870.2869) 
(list 1920.3992 870.2972) 
(list 1920.4141 870.3075) 
(list 1920.4291 870.3178) 
(list 1920.4437 870.3281) 
(list 1920.4574 870.3383) 
(list 1920.47 870.3486) 
(list 1920.4809 870.3589) 
(list 1920.4898 870.3692) 
(list 1920.4965 870.3794) 
(list 1920.5007 870.3897) 
(list 1920.5023 870.4) 
(list 1920.5023 870.4)))
(apply 'command (append '("pline") coords '("c")))
(setq tap6 (ssadd (entlast) tap6))
(command "_mirror" (entlast) "" "1920,900" "1920,901" "No")
(setq tap6 (ssadd (entlast) tap6))
(setq coords (list 
(list 1921.102 870.03) 
(list 1920.5023 870.03) 
(list 1920.5023 870.0403) 
(list 1920.5023 870.0506) 
(list 1920.5023 870.0608) 
(list 1920.5023 870.0711) 
(list 1920.5023 870.0814) 
(list 1920.5023 870.0917) 
(list 1920.5023 870.1019) 
(list 1920.5023 870.1122) 
(list 1920.5023 870.1225) 
(list 1920.5023 870.1328) 
(list 1920.5023 870.1431) 
(list 1920.5023 870.1533) 
(list 1920.5023 870.1636) 
(list 1920.5023 870.1739) 
(list 1920.5023 870.1842) 
(list 1920.5023 870.1944) 
(list 1920.5023 870.2047) 
(list 1920.5023 870.215) 
(list 1920.5023 870.2253) 
(list 1920.5023 870.2356) 
(list 1920.5023 870.2458) 
(list 1920.5023 870.2561) 
(list 1920.5023 870.2664) 
(list 1920.5023 870.2767) 
(list 1920.5023 870.2869) 
(list 1920.5023 870.2972) 
(list 1920.5023 870.3075) 
(list 1920.5023 870.3178) 
(list 1920.5023 870.3281) 
(list 1920.5023 870.3383) 
(list 1920.5023 870.3486) 
(list 1920.5023 870.3589) 
(list 1920.5023 870.3692) 
(list 1920.5023 870.3794) 
(list 1920.5023 870.3897) 
(list 1920.5023 870.4) 
(list 1921.102 870.4)))
(apply 'command (append '("pline") coords '("c")))
(setq tap6 (ssadd (entlast) tap6))
(command "_mirror" (entlast) "" "1920,900" "1920,901" "No")
(setq tap6 (ssadd (entlast) tap6))
(setq coords (list 
(list 1920 870.4) 
(list 1920.125 870.4) 
(list 1920.125 870.4103) 
(list 1920.125 870.4206) 
(list 1920.125 870.4308) 
(list 1920.125 870.4411) 
(list 1920.125 870.4514) 
(list 1920.125 870.4617) 
(list 1920.125 870.4719) 
(list 1920.125 870.4822) 
(list 1920.125 870.4925) 
(list 1920.125 870.5028) 
(list 1920.125 870.5131) 
(list 1920.125 870.5233) 
(list 1920.125 870.5336) 
(list 1920.125 870.5439) 
(list 1920.125 870.5542) 
(list 1920.125 870.5644) 
(list 1920.125 870.5747) 
(list 1920.125 870.585) 
(list 1920.125 870.5953) 
(list 1920.125 870.6056) 
(list 1920.125 870.6158) 
(list 1920.125 870.6261) 
(list 1920.125 870.6364) 
(list 1920.125 870.6467) 
(list 1920.125 870.6569) 
(list 1920.125 870.6672) 
(list 1920.125 870.6775) 
(list 1920.125 870.6878) 
(list 1920.125 870.6981) 
(list 1920.125 870.7083) 
(list 1920.125 870.7186) 
(list 1920.125 870.7289) 
(list 1920.125 870.7392) 
(list 1920.125 870.7494) 
(list 1920.125 870.7597) 
(list 1920.125 870.77) 
(list 1920 870.77)))
(apply 'command (append '("pline") coords '("c")))
(setq tap6 (ssadd (entlast) tap6))
(command "_mirror" (entlast) "" "1920,900" "1920,901" "No")
(setq tap6 (ssadd (entlast) tap6))
(setq coords (list 
(list 1920.5121 870.4) 
(list 1920.5023 870.4) 
(list 1920.5013 870.4103) 
(list 1920.4975 870.4206) 
(list 1920.4913 870.4308) 
(list 1920.4826 870.4411) 
(list 1920.4718 870.4514) 
(list 1920.4592 870.4617) 
(list 1920.4452 870.4719) 
(list 1920.4302 870.4822) 
(list 1920.4146 870.4925) 
(list 1920.3989 870.5028) 
(list 1920.3836 870.5131) 
(list 1920.3692 870.5233) 
(list 1920.3561 870.5336) 
(list 1920.3447 870.5439) 
(list 1920.3353 870.5542) 
(list 1920.3284 870.5644) 
(list 1920.324 870.5747) 
(list 1920.3224 870.585) 
(list 1920.3236 870.5953) 
(list 1920.3276 870.6056) 
(list 1920.3342 870.6158) 
(list 1920.3434 870.6261) 
(list 1920.3547 870.6364) 
(list 1920.368 870.6467) 
(list 1920.3828 870.6569) 
(list 1920.3986 870.6672) 
(list 1920.415 870.6775) 
(list 1920.4315 870.6878) 
(list 1920.4476 870.6981) 
(list 1920.4628 870.7083) 
(list 1920.4766 870.7186) 
(list 1920.4886 870.7289) 
(list 1920.4984 870.7392) 
(list 1920.5057 870.7494) 
(list 1920.5103 870.7597) 
(list 1920.5121 870.77) 
(list 1920.5121 870.77)))
(apply 'command (append '("pline") coords '("c")))
(setq tap6 (ssadd (entlast) tap6))
(command "_mirror" (entlast) "" "1920,900" "1920,901" "No")
(setq tap6 (ssadd (entlast) tap6))
(setq coords (list 
(list 1921.102 870.4) 
(list 1920.5121 870.4) 
(list 1920.5121 870.4103) 
(list 1920.5121 870.4206) 
(list 1920.5121 870.4308) 
(list 1920.5121 870.4411) 
(list 1920.5121 870.4514) 
(list 1920.5121 870.4617) 
(list 1920.5121 870.4719) 
(list 1920.5121 870.4822) 
(list 1920.5121 870.4925) 
(list 1920.5121 870.5028) 
(list 1920.5121 870.5131) 
(list 1920.5121 870.5233) 
(list 1920.5121 870.5336) 
(list 1920.5121 870.5439) 
(list 1920.5121 870.5542) 
(list 1920.5121 870.5644) 
(list 1920.5121 870.5747) 
(list 1920.5121 870.585) 
(list 1920.5121 870.5953) 
(list 1920.5121 870.6056) 
(list 1920.5121 870.6158) 
(list 1920.5121 870.6261) 
(list 1920.5121 870.6364) 
(list 1920.5121 870.6467) 
(list 1920.5121 870.6569) 
(list 1920.5121 870.6672) 
(list 1920.5121 870.6775) 
(list 1920.5121 870.6878) 
(list 1920.5121 870.6981) 
(list 1920.5121 870.7083) 
(list 1920.5121 870.7186) 
(list 1920.5121 870.7289) 
(list 1920.5121 870.7392) 
(list 1920.5121 870.7494) 
(list 1920.5121 870.7597) 
(list 1920.5121 870.77) 
(list 1921.102 870.77)))
(apply 'command (append '("pline") coords '("c")))
(setq tap6 (ssadd (entlast) tap6))
(command "_mirror" (entlast) "" "1920,900" "1920,901" "No")
(setq tap6 (ssadd (entlast) tap6))
(setq coords (list 
(list 1920 870.77) 
(list 1920.125 870.77) 
(list 1920.125 870.7803) 
(list 1920.125 870.7906) 
(list 1920.125 870.8008) 
(list 1920.125 870.8111) 
(list 1920.125 870.8214) 
(list 1920.125 870.8317) 
(list 1920.125 870.8419) 
(list 1920.125 870.8522) 
(list 1920.125 870.8625) 
(list 1920.125 870.8728) 
(list 1920.125 870.8831) 
(list 1920.125 870.8933) 
(list 1920.125 870.9036) 
(list 1920.125 870.9139) 
(list 1920.125 870.9242) 
(list 1920.125 870.9344) 
(list 1920.125 870.9447) 
(list 1920.125 870.955) 
(list 1920.125 870.9653) 
(list 1920.125 870.9756) 
(list 1920.125 870.9858) 
(list 1920.125 870.9961) 
(list 1920.125 871.0064) 
(list 1920.125 871.0167) 
(list 1920.125 871.0269) 
(list 1920.125 871.0372) 
(list 1920.125 871.0475) 
(list 1920.125 871.0578) 
(list 1920.125 871.0681) 
(list 1920.125 871.0783) 
(list 1920.125 871.0886) 
(list 1920.125 871.0989) 
(list 1920.125 871.1092) 
(list 1920.125 871.1194) 
(list 1920.125 871.1297) 
(list 1920.125 871.14) 
(list 1920 871.14)))
(apply 'command (append '("pline") coords '("c")))
(setq tap6 (ssadd (entlast) tap6))
(command "_mirror" (entlast) "" "1920,900" "1920,901" "No")
(setq tap6 (ssadd (entlast) tap6))
(setq coords (list 
(list 1920.5218 870.77) 
(list 1920.5121 870.77) 
(list 1920.5109 870.7803) 
(list 1920.5067 870.7906) 
(list 1920.4998 870.8008) 
(list 1920.4903 870.8111) 
(list 1920.4784 870.8214) 
(list 1920.4646 870.8317) 
(list 1920.4491 870.8419) 
(list 1920.4326 870.8522) 
(list 1920.4155 870.8625) 
(list 1920.3983 870.8728) 
(list 1920.3815 870.8831) 
(list 1920.3657 870.8933) 
(list 1920.3513 870.9036) 
(list 1920.3389 870.9139) 
(list 1920.3286 870.9242) 
(list 1920.321 870.9344) 
(list 1920.3163 870.9447) 
(list 1920.3145 870.955) 
(list 1920.3159 870.9653) 
(list 1920.3202 870.9756) 
(list 1920.3275 870.9858) 
(list 1920.3376 870.9961) 
(list 1920.35 871.0064) 
(list 1920.3646 871.0167) 
(list 1920.3807 871.0269) 
(list 1920.398 871.0372) 
(list 1920.416 871.0475) 
(list 1920.434 871.0578) 
(list 1920.4516 871.0681) 
(list 1920.4681 871.0783) 
(list 1920.4832 871.0886) 
(list 1920.4962 871.0989) 
(list 1920.5069 871.1092) 
(list 1920.5149 871.1194) 
(list 1920.5199 871.1297) 
(list 1920.5218 871.14) 
(list 1920.5218 871.14)))
(apply 'command (append '("pline") coords '("c")))
(setq tap6 (ssadd (entlast) tap6))
(command "_mirror" (entlast) "" "1920,900" "1920,901" "No")
(setq tap6 (ssadd (entlast) tap6))
(setq coords (list 
(list 1921.102 870.77) 
(list 1920.5218 870.77) 
(list 1920.5218 870.7803) 
(list 1920.5218 870.7906) 
(list 1920.5218 870.8008) 
(list 1920.5218 870.8111) 
(list 1920.5218 870.8214) 
(list 1920.5218 870.8317) 
(list 1920.5218 870.8419) 
(list 1920.5218 870.8522) 
(list 1920.5218 870.8625) 
(list 1920.5218 870.8728) 
(list 1920.5218 870.8831) 
(list 1920.5218 870.8933) 
(list 1920.5218 870.9036) 
(list 1920.5218 870.9139) 
(list 1920.5218 870.9242) 
(list 1920.5218 870.9344) 
(list 1920.5218 870.9447) 
(list 1920.5218 870.955) 
(list 1920.5218 870.9653) 
(list 1920.5218 870.9756) 
(list 1920.5218 870.9858) 
(list 1920.5218 870.9961) 
(list 1920.5218 871.0064) 
(list 1920.5218 871.0167) 
(list 1920.5218 871.0269) 
(list 1920.5218 871.0372) 
(list 1920.5218 871.0475) 
(list 1920.5218 871.0578) 
(list 1920.5218 871.0681) 
(list 1920.5218 871.0783) 
(list 1920.5218 871.0886) 
(list 1920.5218 871.0989) 
(list 1920.5218 871.1092) 
(list 1920.5218 871.1194) 
(list 1920.5218 871.1297) 
(list 1920.5218 871.14) 
(list 1921.102 871.14)))
(apply 'command (append '("pline") coords '("c")))
(setq tap6 (ssadd (entlast) tap6))
(command "_mirror" (entlast) "" "1920,900" "1920,901" "No")
(setq tap6 (ssadd (entlast) tap6))
(setq coords (list 
(list 1920 871.14) 
(list 1920.125 871.14) 
(list 1920.125 871.1503) 
(list 1920.125 871.1606) 
(list 1920.125 871.1708) 
(list 1920.125 871.1811) 
(list 1920.125 871.1914) 
(list 1920.125 871.2017) 
(list 1920.125 871.2119) 
(list 1920.125 871.2222) 
(list 1920.125 871.2325) 
(list 1920.125 871.2428) 
(list 1920.125 871.2531) 
(list 1920.125 871.2633) 
(list 1920.125 871.2736) 
(list 1920.125 871.2839) 
(list 1920.125 871.2942) 
(list 1920.125 871.3044) 
(list 1920.125 871.3147) 
(list 1920.125 871.325) 
(list 1920.125 871.3353) 
(list 1920.125 871.3456) 
(list 1920.125 871.3558) 
(list 1920.125 871.3661) 
(list 1920.125 871.3764) 
(list 1920.125 871.3867) 
(list 1920.125 871.3969) 
(list 1920.125 871.4072) 
(list 1920.125 871.4175) 
(list 1920.125 871.4278) 
(list 1920.125 871.4381) 
(list 1920.125 871.4483) 
(list 1920.125 871.4586) 
(list 1920.125 871.4689) 
(list 1920.125 871.4792) 
(list 1920.125 871.4894) 
(list 1920.125 871.4997) 
(list 1920.125 871.51) 
(list 1920 871.51)))
(apply 'command (append '("pline") coords '("c")))
(setq tap6 (ssadd (entlast) tap6))
(command "_mirror" (entlast) "" "1920,900" "1920,901" "No")
(setq tap6 (ssadd (entlast) tap6))
(setq coords (list 
(list 1920.5315 871.14) 
(list 1920.5218 871.14) 
(list 1920.5205 871.1503) 
(list 1920.5159 871.1606) 
(list 1920.5084 871.1708) 
(list 1920.4979 871.1811) 
(list 1920.485 871.1914) 
(list 1920.4699 871.2017) 
(list 1920.4531 871.2119) 
(list 1920.4351 871.2222) 
(list 1920.4164 871.2325) 
(list 1920.3977 871.2428) 
(list 1920.3794 871.2531) 
(list 1920.3622 871.2633) 
(list 1920.3466 871.2736) 
(list 1920.333 871.2839) 
(list 1920.322 871.2942) 
(list 1920.3137 871.3044) 
(list 1920.3086 871.3147) 
(list 1920.3067 871.325) 
(list 1920.3081 871.3353) 
(list 1920.3129 871.3456) 
(list 1920.3208 871.3558) 
(list 1920.3318 871.3661) 
(list 1920.3453 871.3764) 
(list 1920.3611 871.3867) 
(list 1920.3786 871.3969) 
(list 1920.3974 871.4072) 
(list 1920.4169 871.4175) 
(list 1920.4365 871.4278) 
(list 1920.4555 871.4381) 
(list 1920.4734 871.4483) 
(list 1920.4898 871.4586) 
(list 1920.5039 871.4689) 
(list 1920.5155 871.4792) 
(list 1920.5241 871.4894) 
(list 1920.5295 871.4997) 
(list 1920.5315 871.51) 
(list 1920.5315 871.51)))
(apply 'command (append '("pline") coords '("c")))
(setq tap6 (ssadd (entlast) tap6))
(command "_mirror" (entlast) "" "1920,900" "1920,901" "No")
(setq tap6 (ssadd (entlast) tap6))
(setq coords (list 
(list 1921.102 871.14) 
(list 1920.5315 871.14) 
(list 1920.5315 871.1503) 
(list 1920.5315 871.1606) 
(list 1920.5315 871.1708) 
(list 1920.5315 871.1811) 
(list 1920.5315 871.1914) 
(list 1920.5315 871.2017) 
(list 1920.5315 871.2119) 
(list 1920.5315 871.2222) 
(list 1920.5315 871.2325) 
(list 1920.5315 871.2428) 
(list 1920.5315 871.2531) 
(list 1920.5315 871.2633) 
(list 1920.5315 871.2736) 
(list 1920.5315 871.2839) 
(list 1920.5315 871.2942) 
(list 1920.5315 871.3044) 
(list 1920.5315 871.3147) 
(list 1920.5315 871.325) 
(list 1920.5315 871.3353) 
(list 1920.5315 871.3456) 
(list 1920.5315 871.3558) 
(list 1920.5315 871.3661) 
(list 1920.5315 871.3764) 
(list 1920.5315 871.3867) 
(list 1920.5315 871.3969) 
(list 1920.5315 871.4072) 
(list 1920.5315 871.4175) 
(list 1920.5315 871.4278) 
(list 1920.5315 871.4381) 
(list 1920.5315 871.4483) 
(list 1920.5315 871.4586) 
(list 1920.5315 871.4689) 
(list 1920.5315 871.4792) 
(list 1920.5315 871.4894) 
(list 1920.5315 871.4997) 
(list 1920.5315 871.51) 
(list 1921.102 871.51)))
(apply 'command (append '("pline") coords '("c")))
(setq tap6 (ssadd (entlast) tap6))
(command "_mirror" (entlast) "" "1920,900" "1920,901" "No")
(setq tap6 (ssadd (entlast) tap6))
(setq coords (list 
(list 1920 871.51) 
(list 1920.125 871.51) 
(list 1920.125 871.5203) 
(list 1920.125 871.5306) 
(list 1920.125 871.5408) 
(list 1920.125 871.5511) 
(list 1920.125 871.5614) 
(list 1920.125 871.5717) 
(list 1920.125 871.5819) 
(list 1920.125 871.5922) 
(list 1920.125 871.6025) 
(list 1920.125 871.6128) 
(list 1920.125 871.6231) 
(list 1920.125 871.6333) 
(list 1920.125 871.6436) 
(list 1920.125 871.6539) 
(list 1920.125 871.6642) 
(list 1920.125 871.6744) 
(list 1920.125 871.6847) 
(list 1920.125 871.695) 
(list 1920.125 871.7053) 
(list 1920.125 871.7156) 
(list 1920.125 871.7258) 
(list 1920.125 871.7361) 
(list 1920.125 871.7464) 
(list 1920.125 871.7567) 
(list 1920.125 871.7669) 
(list 1920.125 871.7772) 
(list 1920.125 871.7875) 
(list 1920.125 871.7978) 
(list 1920.125 871.8081) 
(list 1920.125 871.8183) 
(list 1920.125 871.8286) 
(list 1920.125 871.8389) 
(list 1920.125 871.8492) 
(list 1920.125 871.8594) 
(list 1920.125 871.8697) 
(list 1920.125 871.88) 
(list 1920 871.88)))
(apply 'command (append '("pline") coords '("c")))
(setq tap6 (ssadd (entlast) tap6))
(command "_mirror" (entlast) "" "1920,900" "1920,901" "No")
(setq tap6 (ssadd (entlast) tap6))
(setq coords (list 
(list 1920.5413 871.51) 
(list 1920.5315 871.51) 
(list 1920.5301 871.5203) 
(list 1920.5251 871.5306) 
(list 1920.5169 871.5408) 
(list 1920.5056 871.5511) 
(list 1920.4916 871.5614) 
(list 1920.4752 871.5717) 
(list 1920.457 871.5819) 
(list 1920.4375 871.5922) 
(list 1920.4174 871.6025) 
(list 1920.3971 871.6128) 
(list 1920.3774 871.6231) 
(list 1920.3588 871.6333) 
(list 1920.3419 871.6436) 
(list 1920.3272 871.6539) 
(list 1920.3153 871.6642) 
(list 1920.3064 871.6744) 
(list 1920.3008 871.6847) 
(list 1920.2988 871.695) 
(list 1920.3004 871.7053) 
(list 1920.3056 871.7156) 
(list 1920.3142 871.7258) 
(list 1920.3259 871.7361) 
(list 1920.3406 871.7464) 
(list 1920.3576 871.7567) 
(list 1920.3766 871.7669) 
(list 1920.3968 871.7772) 
(list 1920.4178 871.7875) 
(list 1920.4389 871.7978) 
(list 1920.4594 871.8081) 
(list 1920.4788 871.8183) 
(list 1920.4963 871.8286) 
(list 1920.5116 871.8389) 
(list 1920.524 871.8492) 
(list 1920.5333 871.8594) 
(list 1920.5391 871.8697) 
(list 1920.5413 871.88) 
(list 1920.5413 871.88)))
(apply 'command (append '("pline") coords '("c")))
(setq tap6 (ssadd (entlast) tap6))
(command "_mirror" (entlast) "" "1920,900" "1920,901" "No")
(setq tap6 (ssadd (entlast) tap6))
(setq coords (list 
(list 1921.102 871.51) 
(list 1920.5413 871.51) 
(list 1920.5413 871.5203) 
(list 1920.5413 871.5306) 
(list 1920.5413 871.5408) 
(list 1920.5413 871.5511) 
(list 1920.5413 871.5614) 
(list 1920.5413 871.5717) 
(list 1920.5413 871.5819) 
(list 1920.5413 871.5922) 
(list 1920.5413 871.6025) 
(list 1920.5413 871.6128) 
(list 1920.5413 871.6231) 
(list 1920.5413 871.6333) 
(list 1920.5413 871.6436) 
(list 1920.5413 871.6539) 
(list 1920.5413 871.6642) 
(list 1920.5413 871.6744) 
(list 1920.5413 871.6847) 
(list 1920.5413 871.695) 
(list 1920.5413 871.7053) 
(list 1920.5413 871.7156) 
(list 1920.5413 871.7258) 
(list 1920.5413 871.7361) 
(list 1920.5413 871.7464) 
(list 1920.5413 871.7567) 
(list 1920.5413 871.7669) 
(list 1920.5413 871.7772) 
(list 1920.5413 871.7875) 
(list 1920.5413 871.7978) 
(list 1920.5413 871.8081) 
(list 1920.5413 871.8183) 
(list 1920.5413 871.8286) 
(list 1920.5413 871.8389) 
(list 1920.5413 871.8492) 
(list 1920.5413 871.8594) 
(list 1920.5413 871.8697) 
(list 1920.5413 871.88) 
(list 1921.102 871.88)))
(apply 'command (append '("pline") coords '("c")))
(setq tap6 (ssadd (entlast) tap6))
(command "_mirror" (entlast) "" "1920,900" "1920,901" "No")
(setq tap6 (ssadd (entlast) tap6))
(setq coords (list 
(list 1920 871.88) 
(list 1920.125 871.88) 
(list 1920.125 871.8903) 
(list 1920.125 871.9006) 
(list 1920.125 871.9108) 
(list 1920.125 871.9211) 
(list 1920.125 871.9314) 
(list 1920.125 871.9417) 
(list 1920.125 871.9519) 
(list 1920.125 871.9622) 
(list 1920.125 871.9725) 
(list 1920.125 871.9828) 
(list 1920.125 871.9931) 
(list 1920.125 872.0033) 
(list 1920.125 872.0136) 
(list 1920.125 872.0239) 
(list 1920.125 872.0342) 
(list 1920.125 872.0444) 
(list 1920.125 872.0547) 
(list 1920.125 872.065) 
(list 1920.125 872.0753) 
(list 1920.125 872.0856) 
(list 1920.125 872.0958) 
(list 1920.125 872.1061) 
(list 1920.125 872.1164) 
(list 1920.125 872.1267) 
(list 1920.125 872.1369) 
(list 1920.125 872.1472) 
(list 1920.125 872.1575) 
(list 1920.125 872.1678) 
(list 1920.125 872.1781) 
(list 1920.125 872.1883) 
(list 1920.125 872.1986) 
(list 1920.125 872.2089) 
(list 1920.125 872.2192) 
(list 1920.125 872.2294) 
(list 1920.125 872.2397) 
(list 1920.125 872.25) 
(list 1920 872.25)))
(apply 'command (append '("pline") coords '("c")))
(setq tap6 (ssadd (entlast) tap6))
(command "_mirror" (entlast) "" "1920,900" "1920,901" "No")
(setq tap6 (ssadd (entlast) tap6))
(setq coords (list 
(list 1920.551 871.88) 
(list 1920.5413 871.88) 
(list 1920.5397 871.8903) 
(list 1920.5343 871.9006) 
(list 1920.5255 871.9108) 
(list 1920.5133 871.9211) 
(list 1920.4982 871.9314) 
(list 1920.4806 871.9417) 
(list 1920.461 871.9519) 
(list 1920.44 871.9622) 
(list 1920.4183 871.9725) 
(list 1920.3965 871.9828) 
(list 1920.3753 871.9931) 
(list 1920.3553 872.0033) 
(list 1920.3372 872.0136) 
(list 1920.3214 872.0239) 
(list 1920.3086 872.0342) 
(list 1920.299 872.0444) 
(list 1920.2931 872.0547) 
(list 1920.2909 872.065) 
(list 1920.2927 872.0753) 
(list 1920.2982 872.0856) 
(list 1920.3075 872.0958) 
(list 1920.3201 872.1061) 
(list 1920.3359 872.1164) 
(list 1920.3542 872.1267) 
(list 1920.3745 872.1369) 
(list 1920.3962 872.1472) 
(list 1920.4188 872.1575) 
(list 1920.4414 872.1678) 
(list 1920.4634 872.1781) 
(list 1920.4841 872.1883) 
(list 1920.5029 872.1986) 
(list 1920.5193 872.2089) 
(list 1920.5326 872.2192) 
(list 1920.5425 872.2294) 
(list 1920.5487 872.2397) 
(list 1920.551 872.25) 
(list 1920.551 872.25)))
(apply 'command (append '("pline") coords '("c")))
(setq tap6 (ssadd (entlast) tap6))
(command "_mirror" (entlast) "" "1920,900" "1920,901" "No")
(setq tap6 (ssadd (entlast) tap6))
(setq coords (list 
(list 1921.102 871.88) 
(list 1920.551 871.88) 
(list 1920.551 871.8903) 
(list 1920.551 871.9006) 
(list 1920.551 871.9108) 
(list 1920.551 871.9211) 
(list 1920.551 871.9314) 
(list 1920.551 871.9417) 
(list 1920.551 871.9519) 
(list 1920.551 871.9622) 
(list 1920.551 871.9725) 
(list 1920.551 871.9828) 
(list 1920.551 871.9931) 
(list 1920.551 872.0033) 
(list 1920.551 872.0136) 
(list 1920.551 872.0239) 
(list 1920.551 872.0342) 
(list 1920.551 872.0444) 
(list 1920.551 872.0547) 
(list 1920.551 872.065) 
(list 1920.551 872.0753) 
(list 1920.551 872.0856) 
(list 1920.551 872.0958) 
(list 1920.551 872.1061) 
(list 1920.551 872.1164) 
(list 1920.551 872.1267) 
(list 1920.551 872.1369) 
(list 1920.551 872.1472) 
(list 1920.551 872.1575) 
(list 1920.551 872.1678) 
(list 1920.551 872.1781) 
(list 1920.551 872.1883) 
(list 1920.551 872.1986) 
(list 1920.551 872.2089) 
(list 1920.551 872.2192) 
(list 1920.551 872.2294) 
(list 1920.551 872.2397) 
(list 1920.551 872.25) 
(list 1921.102 872.25)))
(apply 'command (append '("pline") coords '("c")))
(setq tap6 (ssadd (entlast) tap6))
(command "_mirror" (entlast) "" "1920,900" "1920,901" "No")
(setq tap6 (ssadd (entlast) tap6))
(command "_block" "blktap6" "1920,900" tap6 "")
(command "_insert" "blktap6" "1920,900" "1" "1" "0")
(command "_insert" "blktap6" "1920,900" "1" "1" "180")
(setq uc6 nil)
(setq uc6 (ssadd))
(setq coords (list 
(list 0 -0.185) 
(list 0.125 -0.185) 
(list 0.125 -0.17472) 
(list 0.125 -0.16444) 
(list 0.125 -0.15417) 
(list 0.125 -0.14389) 
(list 0.125 -0.13361) 
(list 0.125 -0.12333) 
(list 0.125 -0.11306) 
(list 0.125 -0.10278) 
(list 0.125 -0.0925) 
(list 0.125 -0.082222) 
(list 0.125 -0.071944) 
(list 0.125 -0.061667) 
(list 0.125 -0.051389) 
(list 0.125 -0.041111) 
(list 0.125 -0.030833) 
(list 0.125 -0.020556) 
(list 0.125 -0.010278) 
(list 0.125 0) 
(list 0.125 0.010278) 
(list 0.125 0.020556) 
(list 0.125 0.030833) 
(list 0.125 0.041111) 
(list 0.125 0.051389) 
(list 0.125 0.061667) 
(list 0.125 0.071944) 
(list 0.125 0.082222) 
(list 0.125 0.0925) 
(list 0.125 0.10278) 
(list 0.125 0.11306) 
(list 0.125 0.12333) 
(list 0.125 0.13361) 
(list 0.125 0.14389) 
(list 0.125 0.15417) 
(list 0.125 0.16444) 
(list 0.125 0.17472) 
(list 0.125 0.185) 
(list 0 0.185)))
(apply 'command (append '("pline") coords '("c")))
(setq uc6 (ssadd (entlast) uc6))
(setq coords (list 
(list 1.102 -0.185) 
(list 0.551 -0.185) 
(list 0.549 -0.17472) 
(list 0.54304 -0.16444) 
(list 0.53331 -0.15417) 
(list 0.52012 -0.14389) 
(list 0.50385 -0.13361) 
(list 0.485 -0.12333) 
(list 0.46415 -0.11306) 
(list 0.44192 -0.10278) 
(list 0.419 -0.0925) 
(list 0.39608 -0.082222) 
(list 0.37385 -0.071944) 
(list 0.353 -0.061667) 
(list 0.33415 -0.051389) 
(list 0.31788 -0.041111) 
(list 0.30468 -0.030833) 
(list 0.29496 -0.020556) 
(list 0.28901 -0.010278) 
(list 0.287 0) 
(list 0.28901 0.010278) 
(list 0.29496 0.020556) 
(list 0.30468 0.030833) 
(list 0.31788 0.041111) 
(list 0.33415 0.051389) 
(list 0.353 0.061667) 
(list 0.37385 0.071944) 
(list 0.39608 0.082222) 
(list 0.419 0.0925) 
(list 0.44192 0.10278) 
(list 0.46415 0.11306) 
(list 0.485 0.12333) 
(list 0.50385 0.13361) 
(list 0.52012 0.14389) 
(list 0.53331 0.15417) 
(list 0.54304 0.16444) 
(list 0.549 0.17472) 
(list 0.551 0.185) 
(list 1.102 0.185)))
(apply 'command (append '("pline") coords '("c")))
(setq uc6 (ssadd (entlast) uc6))
(command "_block" "blkuc6" "0,0.185" uc6 "")
(command "_insert" "blkuc6" "1920,872.62" "1" "1" "0")
(command "_insert" "blkuc6" "1920,872.25" "1" "1" "180")
(command "_insert" "blkuc6" "1920,872.99" "1" "1" "0")
(command "_insert" "blkuc6" "1920,872.62" "1" "1" "180")
(command "_insert" "blkuc6" "1920,873.36" "1" "1" "0")
(command "_insert" "blkuc6" "1920,872.99" "1" "1" "180")
(command "_insert" "blkuc6" "1920,873.73" "1" "1" "0")
(command "_insert" "blkuc6" "1920,873.36" "1" "1" "180")
(command "_insert" "blkuc6" "1920,874.1" "1" "1" "0")
(command "_insert" "blkuc6" "1920,873.73" "1" "1" "180")
(command "_insert" "blkuc6" "1920,874.47" "1" "1" "0")
(command "_insert" "blkuc6" "1920,874.1" "1" "1" "180")
(command "_insert" "blkuc6" "1920,874.84" "1" "1" "0")
(command "_insert" "blkuc6" "1920,874.47" "1" "1" "180")
(command "_insert" "blkuc6" "1920,875.21" "1" "1" "0")
(command "_insert" "blkuc6" "1920,874.84" "1" "1" "180")
(command "_insert" "blkuc6" "1920,875.58" "1" "1" "0")
(command "_insert" "blkuc6" "1920,875.21" "1" "1" "180")
(command "_insert" "blkuc6" "1920,875.95" "1" "1" "0")
(command "_insert" "blkuc6" "1920,875.58" "1" "1" "180")
(command "_insert" "blkuc6" "1920,876.32" "1" "1" "0")
(command "_insert" "blkuc6" "1920,875.95" "1" "1" "180")
(command "_insert" "blkuc6" "1920,876.69" "1" "1" "0")
(command "_insert" "blkuc6" "1920,876.32" "1" "1" "180")
(command "_insert" "blkuc6" "1920,877.06" "1" "1" "0")
(command "_insert" "blkuc6" "1920,876.69" "1" "1" "180")
(command "_insert" "blkuc6" "1920,877.43" "1" "1" "0")
(command "_insert" "blkuc6" "1920,877.06" "1" "1" "180")
(command "_insert" "blkuc6" "1920,877.8" "1" "1" "0")
(command "_insert" "blkuc6" "1920,877.43" "1" "1" "180")
(command "_insert" "blkuc6" "1920,878.17" "1" "1" "0")
(command "_insert" "blkuc6" "1920,877.8" "1" "1" "180")
(command "_insert" "blkuc6" "1920,878.54" "1" "1" "0")
(command "_insert" "blkuc6" "1920,878.17" "1" "1" "180")
(command "_insert" "blkuc6" "1920,878.91" "1" "1" "0")
(command "_insert" "blkuc6" "1920,878.54" "1" "1" "180")
(command "_insert" "blkuc6" "1920,879.28" "1" "1" "0")
(command "_insert" "blkuc6" "1920,878.91" "1" "1" "180")
(command "_insert" "blkuc6" "1920,879.65" "1" "1" "0")
(command "_insert" "blkuc6" "1920,879.28" "1" "1" "180")
(command "_insert" "blkuc6" "1920,880.02" "1" "1" "0")
(command "_insert" "blkuc6" "1920,879.65" "1" "1" "180")
(command "_insert" "blkuc6" "1920,880.39" "1" "1" "0")
(command "_insert" "blkuc6" "1920,880.02" "1" "1" "180")
(command "_insert" "blkuc6" "1920,880.76" "1" "1" "0")
(command "_insert" "blkuc6" "1920,880.39" "1" "1" "180")
(command "_insert" "blkuc6" "1920,881.13" "1" "1" "0")
(command "_insert" "blkuc6" "1920,880.76" "1" "1" "180")
(command "_insert" "blkuc6" "1920,881.5" "1" "1" "0")
(command "_insert" "blkuc6" "1920,881.13" "1" "1" "180")
(command "_insert" "blkuc6" "1920,881.87" "1" "1" "0")
(command "_insert" "blkuc6" "1920,881.5" "1" "1" "180")
(command "_insert" "blkuc6" "1920,882.24" "1" "1" "0")
(command "_insert" "blkuc6" "1920,881.87" "1" "1" "180")
(command "_insert" "blkuc6" "1920,882.61" "1" "1" "0")
(command "_insert" "blkuc6" "1920,882.24" "1" "1" "180")
(command "_insert" "blkuc6" "1920,882.98" "1" "1" "0")
(command "_insert" "blkuc6" "1920,882.61" "1" "1" "180")
(command "_insert" "blkuc6" "1920,883.35" "1" "1" "0")
(command "_insert" "blkuc6" "1920,882.98" "1" "1" "180")
(command "_insert" "blkuc6" "1920,883.72" "1" "1" "0")
(command "_insert" "blkuc6" "1920,883.35" "1" "1" "180")
(command "_insert" "blkuc6" "1920,884.09" "1" "1" "0")
(command "_insert" "blkuc6" "1920,883.72" "1" "1" "180")
(command "_insert" "blkuc6" "1920,884.46" "1" "1" "0")
(command "_insert" "blkuc6" "1920,884.09" "1" "1" "180")
(command "_insert" "blkuc6" "1920,884.83" "1" "1" "0")
(command "_insert" "blkuc6" "1920,884.46" "1" "1" "180")
(command "_insert" "blkuc6" "1920,885.2" "1" "1" "0")
(command "_insert" "blkuc6" "1920,884.83" "1" "1" "180")
(command "_insert" "blkuc6" "1920,885.57" "1" "1" "0")
(command "_insert" "blkuc6" "1920,885.2" "1" "1" "180")
(command "_insert" "blkuc6" "1920,885.94" "1" "1" "0")
(command "_insert" "blkuc6" "1920,885.57" "1" "1" "180")
(command "_insert" "blkuc6" "1920,886.31" "1" "1" "0")
(command "_insert" "blkuc6" "1920,885.94" "1" "1" "180")
(command "_insert" "blkuc6" "1920,886.68" "1" "1" "0")
(command "_insert" "blkuc6" "1920,886.31" "1" "1" "180")
(command "_insert" "blkuc6" "1920,887.05" "1" "1" "0")
(command "_insert" "blkuc6" "1920,886.68" "1" "1" "180")
(command "_insert" "blkuc6" "1920,887.42" "1" "1" "0")
(command "_insert" "blkuc6" "1920,887.05" "1" "1" "180")
(command "_insert" "blkuc6" "1920,887.79" "1" "1" "0")
(command "_insert" "blkuc6" "1920,887.42" "1" "1" "180")
(command "_insert" "blkuc6" "1920,888.16" "1" "1" "0")
(command "_insert" "blkuc6" "1920,887.79" "1" "1" "180")
(command "_insert" "blkuc6" "1920,888.53" "1" "1" "0")
(command "_insert" "blkuc6" "1920,888.16" "1" "1" "180")
(command "_insert" "blkuc6" "1920,888.9" "1" "1" "0")
(command "_insert" "blkuc6" "1920,888.53" "1" "1" "180")
(command "_insert" "blkuc6" "1920,889.27" "1" "1" "0")
(command "_insert" "blkuc6" "1920,888.9" "1" "1" "180")
(command "_insert" "blkuc6" "1920,889.64" "1" "1" "0")
(command "_insert" "blkuc6" "1920,889.27" "1" "1" "180")
(command "_insert" "blkuc6" "1920,890.01" "1" "1" "0")
(command "_insert" "blkuc6" "1920,889.64" "1" "1" "180")
(command "_insert" "blkuc6" "1920,890.38" "1" "1" "0")
(command "_insert" "blkuc6" "1920,890.01" "1" "1" "180")
(command "_insert" "blkuc6" "1920,890.75" "1" "1" "0")
(command "_insert" "blkuc6" "1920,890.38" "1" "1" "180")
(command "_insert" "blkuc6" "1920,891.12" "1" "1" "0")
(command "_insert" "blkuc6" "1920,890.75" "1" "1" "180")
(command "_insert" "blkuc6" "1920,891.49" "1" "1" "0")
(command "_insert" "blkuc6" "1920,891.12" "1" "1" "180")
(command "_insert" "blkuc6" "1920,891.86" "1" "1" "0")
(command "_insert" "blkuc6" "1920,891.49" "1" "1" "180")
(command "_insert" "blkuc6" "1920,892.23" "1" "1" "0")
(command "_insert" "blkuc6" "1920,891.86" "1" "1" "180")
(command "_insert" "blkuc6" "1920,892.6" "1" "1" "0")
(command "_insert" "blkuc6" "1920,892.23" "1" "1" "180")
(command "_insert" "blkuc6" "1920,892.97" "1" "1" "0")
(command "_insert" "blkuc6" "1920,892.6" "1" "1" "180")
(command "_insert" "blkuc6" "1920,893.34" "1" "1" "0")
(command "_insert" "blkuc6" "1920,892.97" "1" "1" "180")
(command "_insert" "blkuc6" "1920,893.71" "1" "1" "0")
(command "_insert" "blkuc6" "1920,893.34" "1" "1" "180")
(command "_insert" "blkuc6" "1920,894.08" "1" "1" "0")
(command "_insert" "blkuc6" "1920,893.71" "1" "1" "180")
(command "_insert" "blkuc6" "1920,894.45" "1" "1" "0")
(command "_insert" "blkuc6" "1920,894.08" "1" "1" "180")
(command "_insert" "blkuc6" "1920,894.82" "1" "1" "0")
(command "_insert" "blkuc6" "1920,894.45" "1" "1" "180")
(command "_insert" "blkuc6" "1920,895.19" "1" "1" "0")
(command "_insert" "blkuc6" "1920,894.82" "1" "1" "180")
(command "_insert" "blkuc6" "1920,895.56" "1" "1" "0")
(command "_insert" "blkuc6" "1920,895.19" "1" "1" "180")
(command "_insert" "blkuc6" "1920,895.93" "1" "1" "0")
(command "_insert" "blkuc6" "1920,895.56" "1" "1" "180")
(command "_insert" "blkuc6" "1920,896.3" "1" "1" "0")
(command "_insert" "blkuc6" "1920,895.93" "1" "1" "180")
(command "_insert" "blkuc6" "1920,896.67" "1" "1" "0")
(command "_insert" "blkuc6" "1920,896.3" "1" "1" "180")
(command "_insert" "blkuc6" "1920,897.04" "1" "1" "0")
(command "_insert" "blkuc6" "1920,896.67" "1" "1" "180")
(command "_insert" "blkuc6" "1920,897.41" "1" "1" "0")
(command "_insert" "blkuc6" "1920,897.04" "1" "1" "180")
(command "_insert" "blkuc6" "1920,897.78" "1" "1" "0")
(command "_insert" "blkuc6" "1920,897.41" "1" "1" "180")
(command "_insert" "blkuc6" "1920,898.15" "1" "1" "0")
(command "_insert" "blkuc6" "1920,897.78" "1" "1" "180")
(command "_insert" "blkuc6" "1920,898.52" "1" "1" "0")
(command "_insert" "blkuc6" "1920,898.15" "1" "1" "180")
(command "_insert" "blkuc6" "1920,898.89" "1" "1" "0")
(command "_insert" "blkuc6" "1920,898.52" "1" "1" "180")
(command "_insert" "blkuc6" "1920,899.26" "1" "1" "0")
(command "_insert" "blkuc6" "1920,898.89" "1" "1" "180")
(command "_insert" "blkuc6" "1920,899.63" "1" "1" "0")
(command "_insert" "blkuc6" "1920,899.26" "1" "1" "180")
(command "_insert" "blkuc6" "1920,900" "1" "1" "0")
(command "_insert" "blkuc6" "1920,899.63" "1" "1" "180")
(command "_insert" "blkuc6" "1920,900.37" "1" "1" "0")
(command "_insert" "blkuc6" "1920,900" "1" "1" "180")
(command "_insert" "blkuc6" "1920,900.74" "1" "1" "0")
(command "_insert" "blkuc6" "1920,900.37" "1" "1" "180")
(command "_insert" "blkuc6" "1920,901.11" "1" "1" "0")
(command "_insert" "blkuc6" "1920,900.74" "1" "1" "180")
(command "_insert" "blkuc6" "1920,901.48" "1" "1" "0")
(command "_insert" "blkuc6" "1920,901.11" "1" "1" "180")
(command "_insert" "blkuc6" "1920,901.85" "1" "1" "0")
(command "_insert" "blkuc6" "1920,901.48" "1" "1" "180")
(command "_insert" "blkuc6" "1920,902.22" "1" "1" "0")
(command "_insert" "blkuc6" "1920,901.85" "1" "1" "180")
(command "_insert" "blkuc6" "1920,902.59" "1" "1" "0")
(command "_insert" "blkuc6" "1920,902.22" "1" "1" "180")
(command "_insert" "blkuc6" "1920,902.96" "1" "1" "0")
(command "_insert" "blkuc6" "1920,902.59" "1" "1" "180")
(command "_insert" "blkuc6" "1920,903.33" "1" "1" "0")
(command "_insert" "blkuc6" "1920,902.96" "1" "1" "180")
(command "_insert" "blkuc6" "1920,903.7" "1" "1" "0")
(command "_insert" "blkuc6" "1920,903.33" "1" "1" "180")
(command "_insert" "blkuc6" "1920,904.07" "1" "1" "0")
(command "_insert" "blkuc6" "1920,903.7" "1" "1" "180")
(command "_insert" "blkuc6" "1920,904.44" "1" "1" "0")
(command "_insert" "blkuc6" "1920,904.07" "1" "1" "180")
(command "_insert" "blkuc6" "1920,904.81" "1" "1" "0")
(command "_insert" "blkuc6" "1920,904.44" "1" "1" "180")
(command "_insert" "blkuc6" "1920,905.18" "1" "1" "0")
(command "_insert" "blkuc6" "1920,904.81" "1" "1" "180")
(command "_insert" "blkuc6" "1920,905.55" "1" "1" "0")
(command "_insert" "blkuc6" "1920,905.18" "1" "1" "180")
(command "_insert" "blkuc6" "1920,905.92" "1" "1" "0")
(command "_insert" "blkuc6" "1920,905.55" "1" "1" "180")
(command "_insert" "blkuc6" "1920,906.29" "1" "1" "0")
(command "_insert" "blkuc6" "1920,905.92" "1" "1" "180")
(command "_insert" "blkuc6" "1920,906.66" "1" "1" "0")
(command "_insert" "blkuc6" "1920,906.29" "1" "1" "180")
(command "_insert" "blkuc6" "1920,907.03" "1" "1" "0")
(command "_insert" "blkuc6" "1920,906.66" "1" "1" "180")
(command "_insert" "blkuc6" "1920,907.4" "1" "1" "0")
(command "_insert" "blkuc6" "1920,907.03" "1" "1" "180")
(command "_insert" "blkuc6" "1920,907.77" "1" "1" "0")
(command "_insert" "blkuc6" "1920,907.4" "1" "1" "180")
(command "_insert" "blkuc6" "1920,908.14" "1" "1" "0")
(command "_insert" "blkuc6" "1920,907.77" "1" "1" "180")
(command "_insert" "blkuc6" "1920,908.51" "1" "1" "0")
(command "_insert" "blkuc6" "1920,908.14" "1" "1" "180")
(command "_insert" "blkuc6" "1920,908.88" "1" "1" "0")
(command "_insert" "blkuc6" "1920,908.51" "1" "1" "180")
(command "_insert" "blkuc6" "1920,909.25" "1" "1" "0")
(command "_insert" "blkuc6" "1920,908.88" "1" "1" "180")
(command "_insert" "blkuc6" "1920,909.62" "1" "1" "0")
(command "_insert" "blkuc6" "1920,909.25" "1" "1" "180")
(command "_insert" "blkuc6" "1920,909.99" "1" "1" "0")
(command "_insert" "blkuc6" "1920,909.62" "1" "1" "180")
(command "_insert" "blkuc6" "1920,910.36" "1" "1" "0")
(command "_insert" "blkuc6" "1920,909.99" "1" "1" "180")
(command "_insert" "blkuc6" "1920,910.73" "1" "1" "0")
(command "_insert" "blkuc6" "1920,910.36" "1" "1" "180")
(command "_insert" "blkuc6" "1920,911.1" "1" "1" "0")
(command "_insert" "blkuc6" "1920,910.73" "1" "1" "180")
(command "_insert" "blkuc6" "1920,911.47" "1" "1" "0")
(command "_insert" "blkuc6" "1920,911.1" "1" "1" "180")
(command "_insert" "blkuc6" "1920,911.84" "1" "1" "0")
(command "_insert" "blkuc6" "1920,911.47" "1" "1" "180")
(command "_insert" "blkuc6" "1920,912.21" "1" "1" "0")
(command "_insert" "blkuc6" "1920,911.84" "1" "1" "180")
(command "_insert" "blkuc6" "1920,912.58" "1" "1" "0")
(command "_insert" "blkuc6" "1920,912.21" "1" "1" "180")
(command "_insert" "blkuc6" "1920,912.95" "1" "1" "0")
(command "_insert" "blkuc6" "1920,912.58" "1" "1" "180")
(command "_insert" "blkuc6" "1920,913.32" "1" "1" "0")
(command "_insert" "blkuc6" "1920,912.95" "1" "1" "180")
(command "_insert" "blkuc6" "1920,913.69" "1" "1" "0")
(command "_insert" "blkuc6" "1920,913.32" "1" "1" "180")
(command "_insert" "blkuc6" "1920,914.06" "1" "1" "0")
(command "_insert" "blkuc6" "1920,913.69" "1" "1" "180")
(command "_insert" "blkuc6" "1920,914.43" "1" "1" "0")
(command "_insert" "blkuc6" "1920,914.06" "1" "1" "180")
(command "_insert" "blkuc6" "1920,914.8" "1" "1" "0")
(command "_insert" "blkuc6" "1920,914.43" "1" "1" "180")
(command "_insert" "blkuc6" "1920,915.17" "1" "1" "0")
(command "_insert" "blkuc6" "1920,914.8" "1" "1" "180")
(command "_insert" "blkuc6" "1920,915.54" "1" "1" "0")
(command "_insert" "blkuc6" "1920,915.17" "1" "1" "180")
(command "_insert" "blkuc6" "1920,915.91" "1" "1" "0")
(command "_insert" "blkuc6" "1920,915.54" "1" "1" "180")
(command "_insert" "blkuc6" "1920,916.28" "1" "1" "0")
(command "_insert" "blkuc6" "1920,915.91" "1" "1" "180")
(command "_insert" "blkuc6" "1920,916.65" "1" "1" "0")
(command "_insert" "blkuc6" "1920,916.28" "1" "1" "180")
(command "_insert" "blkuc6" "1920,917.02" "1" "1" "0")
(command "_insert" "blkuc6" "1920,916.65" "1" "1" "180")
(command "_insert" "blkuc6" "1920,917.39" "1" "1" "0")
(command "_insert" "blkuc6" "1920,917.02" "1" "1" "180")
(command "_insert" "blkuc6" "1920,917.76" "1" "1" "0")
(command "_insert" "blkuc6" "1920,917.39" "1" "1" "180")
(command "_insert" "blkuc6" "1920,918.13" "1" "1" "0")
(command "_insert" "blkuc6" "1920,917.76" "1" "1" "180")
(command "_insert" "blkuc6" "1920,918.5" "1" "1" "0")
(command "_insert" "blkuc6" "1920,918.13" "1" "1" "180")
(command "_insert" "blkuc6" "1920,918.87" "1" "1" "0")
(command "_insert" "blkuc6" "1920,918.5" "1" "1" "180")
(command "_insert" "blkuc6" "1920,919.24" "1" "1" "0")
(command "_insert" "blkuc6" "1920,918.87" "1" "1" "180")
(command "_insert" "blkuc6" "1920,919.61" "1" "1" "0")
(command "_insert" "blkuc6" "1920,919.24" "1" "1" "180")
(command "_insert" "blkuc6" "1920,919.98" "1" "1" "0")
(command "_insert" "blkuc6" "1920,919.61" "1" "1" "180")
(command "_insert" "blkuc6" "1920,920.35" "1" "1" "0")
(command "_insert" "blkuc6" "1920,919.98" "1" "1" "180")
(command "_insert" "blkuc6" "1920,920.72" "1" "1" "0")
(command "_insert" "blkuc6" "1920,920.35" "1" "1" "180")
(command "_insert" "blkuc6" "1920,921.09" "1" "1" "0")
(command "_insert" "blkuc6" "1920,920.72" "1" "1" "180")
(command "_insert" "blkuc6" "1920,921.46" "1" "1" "0")
(command "_insert" "blkuc6" "1920,921.09" "1" "1" "180")
(command "_insert" "blkuc6" "1920,921.83" "1" "1" "0")
(command "_insert" "blkuc6" "1920,921.46" "1" "1" "180")
(command "_insert" "blkuc6" "1920,922.2" "1" "1" "0")
(command "_insert" "blkuc6" "1920,921.83" "1" "1" "180")
(command "_insert" "blkuc6" "1920,922.57" "1" "1" "0")
(command "_insert" "blkuc6" "1920,922.2" "1" "1" "180")
(command "_insert" "blkuc6" "1920,922.94" "1" "1" "0")
(command "_insert" "blkuc6" "1920,922.57" "1" "1" "180")
(command "_insert" "blkuc6" "1920,923.31" "1" "1" "0")
(command "_insert" "blkuc6" "1920,922.94" "1" "1" "180")
(command "_insert" "blkuc6" "1920,923.68" "1" "1" "0")
(command "_insert" "blkuc6" "1920,923.31" "1" "1" "180")
(command "_insert" "blkuc6" "1920,924.05" "1" "1" "0")
(command "_insert" "blkuc6" "1920,923.68" "1" "1" "180")
(command "_insert" "blkuc6" "1920,924.42" "1" "1" "0")
(command "_insert" "blkuc6" "1920,924.05" "1" "1" "180")
(command "_insert" "blkuc6" "1920,924.79" "1" "1" "0")
(command "_insert" "blkuc6" "1920,924.42" "1" "1" "180")
(command "_insert" "blkuc6" "1920,925.16" "1" "1" "0")
(command "_insert" "blkuc6" "1920,924.79" "1" "1" "180")
(command "_insert" "blkuc6" "1920,925.53" "1" "1" "0")
(command "_insert" "blkuc6" "1920,925.16" "1" "1" "180")
(command "_insert" "blkuc6" "1920,925.9" "1" "1" "0")
(command "_insert" "blkuc6" "1920,925.53" "1" "1" "180")
(command "_insert" "blkuc6" "1920,926.27" "1" "1" "0")
(command "_insert" "blkuc6" "1920,925.9" "1" "1" "180")
(command "_insert" "blkuc6" "1920,926.64" "1" "1" "0")
(command "_insert" "blkuc6" "1920,926.27" "1" "1" "180")
(command "_insert" "blkuc6" "1920,927.01" "1" "1" "0")
(command "_insert" "blkuc6" "1920,926.64" "1" "1" "180")
(command "_insert" "blkuc6" "1920,927.38" "1" "1" "0")
(command "_insert" "blkuc6" "1920,927.01" "1" "1" "180")
(command "_insert" "blkuc6" "1920,927.75" "1" "1" "0")
(command "_insert" "blkuc6" "1920,927.38" "1" "1" "180")
(command "_layer" "set" "phccover" "")
(command "_rectangle" "1918.898,933.3" "1921.102,866.7")
(command "_layer" "set" "nitride" "")
(setq phc6 currobj)
(command "_layer" "set" "cover" "")
(command "_rectangle" "1918.898,836.7" "1921.102,963.3")
(command "_layer" "set" "nitride" "")
(command "_layer" "set" "text" "")
(command "_circle" "1917.948,846.7" "0.075")
(command "_circle" "1917.573,846.7" "0.15")
(command "_circle" "1917.198,846.7" "0.075")
(command "_circle" "1916.823,846.7" "0.15")
(command "_circle" "1917.948,848.7" "0.075")
(command "_circle" "1917.573,848.7" "0.075")
(command "_circle" "1917.198,848.7" "0.15")
(command "_circle" "1916.823,848.7" "0.15")
(command "_circle" "1917.948,850.7" "0.075")
(command "_circle" "1917.573,850.7" "0.15")
(command "_circle" "1917.198,850.7" "0.15")
(command "_circle" "1916.823,850.7" "0.15")
(command "_circle" "1917.948,852.7" "0.075")
(command "_circle" "1917.573,852.7" "0.075")
(command "_circle" "1917.198,852.7" "0.075")
(command "_circle" "1916.823,852.7" "0.075")
(command "_circle" "1916.448,852.7" "0.15")
(command "_circle" "1917.948,854.7" "0.075")
(command "_circle" "1917.573,854.7" "0.15")
(command "_circle" "1917.198,854.7" "0.075")
(command "_circle" "1916.823,854.7" "0.075")
(command "_circle" "1916.448,854.7" "0.15")
(command "_circle" "1917.948,856.7" "0.075")
(command "_circle" "1917.573,856.7" "0.075")
(command "_circle" "1917.198,856.7" "0.15")
(command "_circle" "1916.823,856.7" "0.075")
(command "_circle" "1916.448,856.7" "0.15")
(command "_circle" "1917.948,858.7" "0.075")
(command "_circle" "1917.573,858.7" "0.15")
(command "_circle" "1917.198,858.7" "0.15")
(command "_circle" "1916.823,858.7" "0.075")
(command "_circle" "1916.448,858.7" "0.15")
(command "_circle" "1917.948,860.7" "0.075")
(command "_circle" "1917.573,860.7" "0.075")
(command "_circle" "1917.198,860.7" "0.075")
(command "_circle" "1916.823,860.7" "0.15")
(command "_circle" "1916.448,860.7" "0.15")
(command "_circle" "1917.948,862.7" "0.075")
(command "_circle" "1917.573,862.7" "0.15")
(command "_circle" "1917.198,862.7" "0.075")
(command "_circle" "1916.823,862.7" "0.15")
(command "_circle" "1916.448,862.7" "0.15")
(command "_circle" "1917.948,864.7" "0.075")
(command "_circle" "1917.573,864.7" "0.075")
(command "_circle" "1917.198,864.7" "0.15")
(command "_circle" "1916.823,864.7" "0.15")
(command "_circle" "1916.448,864.7" "0.15")
(command "_circle" "1917.948,866.7" "0.075")
(command "_circle" "1917.573,866.7" "0.15")
(command "_circle" "1917.198,866.7" "0.15")
(command "_circle" "1916.823,866.7" "0.15")
(command "_circle" "1916.448,866.7" "0.15")
(command "_circle" "1917.948,868.7" "0.075")
(command "_circle" "1917.573,868.7" "0.075")
(command "_circle" "1917.198,868.7" "0.075")
(command "_circle" "1916.823,868.7" "0.075")
(command "_circle" "1916.448,868.7" "0.075")
(command "_circle" "1916.073,868.7" "0.15")
(command "_circle" "1917.948,870.7" "0.075")
(command "_circle" "1917.573,870.7" "0.15")
(command "_circle" "1917.198,870.7" "0.075")
(command "_circle" "1916.823,870.7" "0.075")
(command "_circle" "1916.448,870.7" "0.075")
(command "_circle" "1916.073,870.7" "0.15")
(command "_circle" "1917.948,872.7" "0.075")
(command "_circle" "1917.573,872.7" "0.075")
(command "_circle" "1917.198,872.7" "0.15")
(command "_circle" "1916.823,872.7" "0.075")
(command "_circle" "1916.448,872.7" "0.075")
(command "_circle" "1916.073,872.7" "0.15")
(command "_circle" "1917.948,874.7" "0.075")
(command "_circle" "1917.573,874.7" "0.15")
(command "_circle" "1917.198,874.7" "0.15")
(command "_circle" "1916.823,874.7" "0.075")
(command "_circle" "1916.448,874.7" "0.075")
(command "_circle" "1916.073,874.7" "0.15")
(command "_circle" "1917.948,876.7" "0.075")
(command "_circle" "1917.573,876.7" "0.075")
(command "_circle" "1917.198,876.7" "0.075")
(command "_circle" "1916.823,876.7" "0.15")
(command "_circle" "1916.448,876.7" "0.075")
(command "_circle" "1916.073,876.7" "0.15")
(command "_circle" "1917.948,878.7" "0.075")
(command "_circle" "1917.573,878.7" "0.15")
(command "_circle" "1917.198,878.7" "0.075")
(command "_circle" "1916.823,878.7" "0.15")
(command "_circle" "1916.448,878.7" "0.075")
(command "_circle" "1916.073,878.7" "0.15")
(command "_circle" "1917.948,880.7" "0.075")
(command "_circle" "1917.573,880.7" "0.075")
(command "_circle" "1917.198,880.7" "0.15")
(command "_circle" "1916.823,880.7" "0.15")
(command "_circle" "1916.448,880.7" "0.075")
(command "_circle" "1916.073,880.7" "0.15")
(command "_circle" "1917.948,882.7" "0.075")
(command "_circle" "1917.573,882.7" "0.15")
(command "_circle" "1917.198,882.7" "0.15")
(command "_circle" "1916.823,882.7" "0.15")
(command "_circle" "1916.448,882.7" "0.075")
(command "_circle" "1916.073,882.7" "0.15")
(command "_circle" "1917.948,884.7" "0.075")
(command "_circle" "1917.573,884.7" "0.075")
(command "_circle" "1917.198,884.7" "0.075")
(command "_circle" "1916.823,884.7" "0.075")
(command "_circle" "1916.448,884.7" "0.15")
(command "_circle" "1916.073,884.7" "0.15")
(command "_circle" "1917.948,886.7" "0.075")
(command "_circle" "1917.573,886.7" "0.15")
(command "_circle" "1917.198,886.7" "0.075")
(command "_circle" "1916.823,886.7" "0.075")
(command "_circle" "1916.448,886.7" "0.15")
(command "_circle" "1916.073,886.7" "0.15")
(command "_circle" "1917.948,888.7" "0.075")
(command "_circle" "1917.573,888.7" "0.075")
(command "_circle" "1917.198,888.7" "0.15")
(command "_circle" "1916.823,888.7" "0.075")
(command "_circle" "1916.448,888.7" "0.15")
(command "_circle" "1916.073,888.7" "0.15")
(command "_circle" "1917.948,890.7" "0.075")
(command "_circle" "1917.573,890.7" "0.15")
(command "_circle" "1917.198,890.7" "0.15")
(command "_circle" "1916.823,890.7" "0.075")
(command "_circle" "1916.448,890.7" "0.15")
(command "_circle" "1916.073,890.7" "0.15")
(command "_circle" "1917.948,892.7" "0.075")
(command "_circle" "1917.573,892.7" "0.075")
(command "_circle" "1917.198,892.7" "0.075")
(command "_circle" "1916.823,892.7" "0.15")
(command "_circle" "1916.448,892.7" "0.15")
(command "_circle" "1916.073,892.7" "0.15")
(command "_circle" "1917.948,894.7" "0.075")
(command "_circle" "1917.573,894.7" "0.15")
(command "_circle" "1917.198,894.7" "0.075")
(command "_circle" "1916.823,894.7" "0.15")
(command "_circle" "1916.448,894.7" "0.15")
(command "_circle" "1916.073,894.7" "0.15")
(command "_circle" "1917.948,896.7" "0.075")
(command "_circle" "1917.573,896.7" "0.075")
(command "_circle" "1917.198,896.7" "0.15")
(command "_circle" "1916.823,896.7" "0.15")
(command "_circle" "1916.448,896.7" "0.15")
(command "_circle" "1916.073,896.7" "0.15")
(command "_circle" "1917.948,898.7" "0.075")
(command "_circle" "1917.573,898.7" "0.15")
(command "_circle" "1917.198,898.7" "0.15")
(command "_circle" "1916.823,898.7" "0.15")
(command "_circle" "1916.448,898.7" "0.15")
(command "_circle" "1916.073,898.7" "0.15")
(command "_circle" "1917.948,900.7" "0.075")
(command "_circle" "1917.573,900.7" "0.075")
(command "_circle" "1917.198,900.7" "0.075")
(command "_circle" "1916.823,900.7" "0.075")
(command "_circle" "1916.448,900.7" "0.075")
(command "_circle" "1916.073,900.7" "0.075")
(command "_circle" "1915.698,900.7" "0.15")
(command "_circle" "1917.948,902.7" "0.075")
(command "_circle" "1917.573,902.7" "0.15")
(command "_circle" "1917.198,902.7" "0.075")
(command "_circle" "1916.823,902.7" "0.075")
(command "_circle" "1916.448,902.7" "0.075")
(command "_circle" "1916.073,902.7" "0.075")
(command "_circle" "1915.698,902.7" "0.15")
(command "_circle" "1917.948,904.7" "0.075")
(command "_circle" "1917.573,904.7" "0.075")
(command "_circle" "1917.198,904.7" "0.15")
(command "_circle" "1916.823,904.7" "0.075")
(command "_circle" "1916.448,904.7" "0.075")
(command "_circle" "1916.073,904.7" "0.075")
(command "_circle" "1915.698,904.7" "0.15")
(command "_circle" "1917.948,906.7" "0.075")
(command "_circle" "1917.573,906.7" "0.15")
(command "_circle" "1917.198,906.7" "0.15")
(command "_circle" "1916.823,906.7" "0.075")
(command "_circle" "1916.448,906.7" "0.075")
(command "_circle" "1916.073,906.7" "0.075")
(command "_circle" "1915.698,906.7" "0.15")
(command "_circle" "1917.948,908.7" "0.075")
(command "_circle" "1917.573,908.7" "0.075")
(command "_circle" "1917.198,908.7" "0.075")
(command "_circle" "1916.823,908.7" "0.15")
(command "_circle" "1916.448,908.7" "0.075")
(command "_circle" "1916.073,908.7" "0.075")
(command "_circle" "1915.698,908.7" "0.15")
(command "_circle" "1917.948,910.7" "0.075")
(command "_circle" "1917.573,910.7" "0.15")
(command "_circle" "1917.198,910.7" "0.075")
(command "_circle" "1916.823,910.7" "0.15")
(command "_circle" "1916.448,910.7" "0.075")
(command "_circle" "1916.073,910.7" "0.075")
(command "_circle" "1915.698,910.7" "0.15")
(command "_circle" "1917.948,912.7" "0.075")
(command "_circle" "1917.573,912.7" "0.075")
(command "_circle" "1917.198,912.7" "0.15")
(command "_circle" "1916.823,912.7" "0.15")
(command "_circle" "1916.448,912.7" "0.075")
(command "_circle" "1916.073,912.7" "0.075")
(command "_circle" "1915.698,912.7" "0.15")
(command "_circle" "1917.948,914.7" "0.075")
(command "_circle" "1917.573,914.7" "0.15")
(command "_circle" "1917.198,914.7" "0.15")
(command "_circle" "1916.823,914.7" "0.15")
(command "_circle" "1916.448,914.7" "0.075")
(command "_circle" "1916.073,914.7" "0.075")
(command "_circle" "1915.698,914.7" "0.15")
(command "_circle" "1917.948,916.7" "0.075")
(command "_circle" "1917.573,916.7" "0.075")
(command "_circle" "1917.198,916.7" "0.075")
(command "_circle" "1916.823,916.7" "0.075")
(command "_circle" "1916.448,916.7" "0.15")
(command "_circle" "1916.073,916.7" "0.075")
(command "_circle" "1915.698,916.7" "0.15")
(command "_circle" "1917.948,918.7" "0.075")
(command "_circle" "1917.573,918.7" "0.15")
(command "_circle" "1917.198,918.7" "0.075")
(command "_circle" "1916.823,918.7" "0.075")
(command "_circle" "1916.448,918.7" "0.15")
(command "_circle" "1916.073,918.7" "0.075")
(command "_circle" "1915.698,918.7" "0.15")
(command "_circle" "1917.948,920.7" "0.075")
(command "_circle" "1917.573,920.7" "0.075")
(command "_circle" "1917.198,920.7" "0.15")
(command "_circle" "1916.823,920.7" "0.075")
(command "_circle" "1916.448,920.7" "0.15")
(command "_circle" "1916.073,920.7" "0.075")
(command "_circle" "1915.698,920.7" "0.15")
(command "_circle" "1917.948,922.7" "0.075")
(command "_circle" "1917.573,922.7" "0.15")
(command "_circle" "1917.198,922.7" "0.15")
(command "_circle" "1916.823,922.7" "0.075")
(command "_circle" "1916.448,922.7" "0.15")
(command "_circle" "1916.073,922.7" "0.075")
(command "_circle" "1915.698,922.7" "0.15")
(command "_circle" "1917.948,924.7" "0.075")
(command "_circle" "1917.573,924.7" "0.075")
(command "_circle" "1917.198,924.7" "0.075")
(command "_circle" "1916.823,924.7" "0.15")
(command "_circle" "1916.448,924.7" "0.15")
(command "_circle" "1916.073,924.7" "0.075")
(command "_circle" "1915.698,924.7" "0.15")
(command "_circle" "1917.948,926.7" "0.075")
(command "_circle" "1917.573,926.7" "0.15")
(command "_circle" "1917.198,926.7" "0.075")
(command "_circle" "1916.823,926.7" "0.15")
(command "_circle" "1916.448,926.7" "0.15")
(command "_circle" "1916.073,926.7" "0.075")
(command "_circle" "1915.698,926.7" "0.15")
(command "_circle" "1917.948,928.7" "0.075")
(command "_circle" "1917.573,928.7" "0.075")
(command "_circle" "1917.198,928.7" "0.15")
(command "_circle" "1916.823,928.7" "0.15")
(command "_circle" "1916.448,928.7" "0.15")
(command "_circle" "1916.073,928.7" "0.075")
(command "_circle" "1915.698,928.7" "0.15")
(command "_circle" "1917.948,930.7" "0.075")
(command "_circle" "1917.573,930.7" "0.15")
(command "_circle" "1917.198,930.7" "0.15")
(command "_circle" "1916.823,930.7" "0.15")
(command "_circle" "1916.448,930.7" "0.15")
(command "_circle" "1916.073,930.7" "0.075")
(command "_circle" "1915.698,930.7" "0.15")
(command "_circle" "1917.948,932.7" "0.075")
(command "_circle" "1917.573,932.7" "0.075")
(command "_circle" "1917.198,932.7" "0.075")
(command "_circle" "1916.823,932.7" "0.075")
(command "_circle" "1916.448,932.7" "0.075")
(command "_circle" "1916.073,932.7" "0.15")
(command "_circle" "1915.698,932.7" "0.15")
(command "_circle" "1917.948,934.7" "0.075")
(command "_circle" "1917.573,934.7" "0.15")
(command "_circle" "1917.198,934.7" "0.075")
(command "_circle" "1916.823,934.7" "0.075")
(command "_circle" "1916.448,934.7" "0.075")
(command "_circle" "1916.073,934.7" "0.15")
(command "_circle" "1915.698,934.7" "0.15")
(command "_circle" "1917.948,936.7" "0.075")
(command "_circle" "1917.573,936.7" "0.075")
(command "_circle" "1917.198,936.7" "0.15")
(command "_circle" "1916.823,936.7" "0.075")
(command "_circle" "1916.448,936.7" "0.075")
(command "_circle" "1916.073,936.7" "0.15")
(command "_circle" "1915.698,936.7" "0.15")
(command "_circle" "1917.948,938.7" "0.075")
(command "_circle" "1917.573,938.7" "0.15")
(command "_circle" "1917.198,938.7" "0.15")
(command "_circle" "1916.823,938.7" "0.075")
(command "_circle" "1916.448,938.7" "0.075")
(command "_circle" "1916.073,938.7" "0.15")
(command "_circle" "1915.698,938.7" "0.15")
(command "_circle" "1917.948,940.7" "0.075")
(command "_circle" "1917.573,940.7" "0.075")
(command "_circle" "1917.198,940.7" "0.075")
(command "_circle" "1916.823,940.7" "0.15")
(command "_circle" "1916.448,940.7" "0.075")
(command "_circle" "1916.073,940.7" "0.15")
(command "_circle" "1915.698,940.7" "0.15")
(command "_circle" "1917.948,942.7" "0.075")
(command "_circle" "1917.573,942.7" "0.15")
(command "_circle" "1917.198,942.7" "0.075")
(command "_circle" "1916.823,942.7" "0.15")
(command "_circle" "1916.448,942.7" "0.075")
(command "_circle" "1916.073,942.7" "0.15")
(command "_circle" "1915.698,942.7" "0.15")
(command "_circle" "1917.948,944.7" "0.075")
(command "_circle" "1917.573,944.7" "0.075")
(command "_circle" "1917.198,944.7" "0.15")
(command "_circle" "1916.823,944.7" "0.15")
(command "_circle" "1916.448,944.7" "0.075")
(command "_circle" "1916.073,944.7" "0.15")
(command "_circle" "1915.698,944.7" "0.15")
(command "_circle" "1917.948,946.7" "0.075")
(command "_circle" "1917.573,946.7" "0.15")
(command "_circle" "1917.198,946.7" "0.15")
(command "_circle" "1916.823,946.7" "0.15")
(command "_circle" "1916.448,946.7" "0.075")
(command "_circle" "1916.073,946.7" "0.15")
(command "_circle" "1915.698,946.7" "0.15")
(command "_circle" "1917.948,948.7" "0.075")
(command "_circle" "1917.573,948.7" "0.075")
(command "_circle" "1917.198,948.7" "0.075")
(command "_circle" "1916.823,948.7" "0.075")
(command "_circle" "1916.448,948.7" "0.15")
(command "_circle" "1916.073,948.7" "0.15")
(command "_circle" "1915.698,948.7" "0.15")
(command "_circle" "1917.948,950.7" "0.075")
(command "_circle" "1917.573,950.7" "0.15")
(command "_circle" "1917.198,950.7" "0.075")
(command "_circle" "1916.823,950.7" "0.075")
(command "_circle" "1916.448,950.7" "0.15")
(command "_circle" "1916.073,950.7" "0.15")
(command "_circle" "1915.698,950.7" "0.15")
(command "_circle" "1917.948,952.7" "0.075")
(command "_circle" "1917.573,952.7" "0.075")
(command "_circle" "1917.198,952.7" "0.15")
(command "_circle" "1916.823,952.7" "0.075")
(command "_circle" "1916.448,952.7" "0.15")
(command "_circle" "1916.073,952.7" "0.15")
(command "_circle" "1915.698,952.7" "0.15")
(command "_circle" "1917.948,954.7" "0.075")
(command "_circle" "1917.573,954.7" "0.15")
(command "_circle" "1917.198,954.7" "0.15")
(command "_circle" "1916.823,954.7" "0.075")
(command "_circle" "1916.448,954.7" "0.15")
(command "_circle" "1916.073,954.7" "0.15")
(command "_circle" "1915.698,954.7" "0.15")
(command "_circle" "1917.948,956.7" "0.075")
(command "_circle" "1917.573,956.7" "0.075")
(command "_circle" "1917.198,956.7" "0.075")
(command "_circle" "1916.823,956.7" "0.15")
(command "_circle" "1916.448,956.7" "0.15")
(command "_circle" "1916.073,956.7" "0.15")
(command "_circle" "1915.698,956.7" "0.15")
(command "_circle" "1917.948,958.7" "0.075")
(command "_circle" "1917.573,958.7" "0.15")
(command "_circle" "1917.198,958.7" "0.075")
(command "_circle" "1916.823,958.7" "0.15")
(command "_circle" "1916.448,958.7" "0.15")
(command "_circle" "1916.073,958.7" "0.15")
(command "_circle" "1915.698,958.7" "0.15")
(command "_circle" "1917.948,960.7" "0.075")
(command "_circle" "1917.573,960.7" "0.075")
(command "_circle" "1917.198,960.7" "0.15")
(command "_circle" "1916.823,960.7" "0.15")
(command "_circle" "1916.448,960.7" "0.15")
(command "_circle" "1916.073,960.7" "0.15")
(command "_circle" "1915.698,960.7" "0.15")
(command "_circle" "1917.948,962.7" "0.075")
(command "_circle" "1917.573,962.7" "0.15")
(command "_circle" "1917.198,962.7" "0.15")
(command "_circle" "1916.823,962.7" "0.15")
(command "_circle" "1916.448,962.7" "0.15")
(command "_circle" "1916.073,962.7" "0.15")
(command "_circle" "1915.698,962.7" "0.15")
(command "_layer" "set" "nitride" "")
(command "_layer" "set" "text" "")
(command-s "_text" "1906.898,963.3" "2" "-90" "a = 370 nm" )
(sssetfirst nil (ssget "_L"))
(if (not (numberp (vl-string-search "Mac" (getvar "platform")))) (c:txtexp))
(command "_layer" "set" "nitride" "")
(command "_layer" "set" "text" "")
(command-s "_text" "1903.898,963.3" "2" "-90" "gap = 250 nm" )
(sssetfirst nil (ssget "_L"))
(if (not (numberp (vl-string-search "Mac" (getvar "platform")))) (c:txtexp))
(command "_layer" "set" "nitride" "")
(command "_layer" "set" "text" "")
(command-s "_text" "1900.898,963.3" "2" "-90" "amplitude = 132 nm" )
(sssetfirst nil (ssget "_L"))
(if (not (numberp (vl-string-search "Mac" (getvar "platform")))) (c:txtexp))
(command "_layer" "set" "nitride" "")
(command "_layer" "set" "text" "")
(command-s "_text" "1897.898,963.3" "2" "-90" "start width = 280 nm" )
(sssetfirst nil (ssget "_L"))
(if (not (numberp (vl-string-search "Mac" (getvar "platform")))) (c:txtexp))
(command "_layer" "set" "nitride" "")
(command "_layer" "set" "text" "")
(command-s "_text" "1894.898,963.3" "2" "-90" "width = 294 nm" )
(sssetfirst nil (ssget "_L"))
(if (not (numberp (vl-string-search "Mac" (getvar "platform")))) (c:txtexp))
(command "_layer" "set" "nitride" "")
(command "_layer" "set" "text" "")
(command-s "_text" "1891.898,963.3" "2" "-90" "taper: 15" )
(sssetfirst nil (ssget "_L"))
(if (not (numberp (vl-string-search "Mac" (getvar "platform")))) (c:txtexp))
(command "_layer" "set" "nitride" "")
(command "_layer" "set" "text" "")
(command-s "_text" "1888.898,963.3" "2" "-90" "nominal: 150" )
(sssetfirst nil (ssget "_L"))
(if (not (numberp (vl-string-search "Mac" (getvar "platform")))) (c:txtexp))
(command "_layer" "set" "nitride" "")
(command "_layer" "set" "indicators" "")
(setq coords (list 
(list 1840.415 940) 
(list 1840.415 920) 
(list 1820.415 900) 
(list 1840.415 880) 
(list 1840.415 860) 
(list 1840.415 900) 
(list 1840.415 887.0711) 
(list 1827.4861 900) 
(list 1840.415 912.9289) 
(list 1840.415 900)))
(apply 'command (append '("pline") coords '("c")))
(command "._fillet" "radius" "1" "._fillet" "P" (entlast))
(setq coords (list 
(list 1999.585 940) 
(list 1999.585 920) 
(list 2019.585 900) 
(list 1999.585 880) 
(list 1999.585 860) 
(list 1999.585 900) 
(list 1999.585 887.0711) 
(list 2012.5139 900) 
(list 1999.585 912.9289) 
(list 1999.585 900)))
(apply 'command (append '("pline") coords '("c")))
(command "._fillet" "radius" "1" "._fillet" "P" (entlast))
(command "_layer" "set" "holes" "")
(command "_circle" "1838.0629,914.1124" "0.5")
(command "_circle" "1835.7109,911.7603" "0.5")
(command "_circle" "1833.3588,909.4083" "0.5")
(command "_circle" "1831.0067,907.0562" "0.5")
(command "_circle" "1828.6547,904.7041" "0.5")
(command "_circle" "1826.3026,902.3521" "0.5")
(command "_circle" "1823.9505,900" "0.5")
(command "_circle" "1826.3026,897.6479" "0.5")
(command "_circle" "1828.6547,895.2959" "0.5")
(command "_circle" "1831.0067,892.9438" "0.5")
(command "_circle" "1833.3588,890.5917" "0.5")
(command "_circle" "1835.7109,888.2397" "0.5")
(command "_circle" "1838.0629,885.8876" "0.5")
(command "_circle" "2001.9371,914.1124" "0.5")
(command "_circle" "2004.2891,911.7603" "0.5")
(command "_circle" "2006.6412,909.4083" "0.5")
(command "_circle" "2008.9933,907.0562" "0.5")
(command "_circle" "2011.3453,904.7041" "0.5")
(command "_circle" "2013.6974,902.3521" "0.5")
(command "_circle" "2016.0495,900" "0.5")
(command "_circle" "2013.6974,897.6479" "0.5")
(command "_circle" "2011.3453,895.2959" "0.5")
(command "_circle" "2008.9933,892.9438" "0.5")
(command "_circle" "2006.6412,890.5917" "0.5")
(command "_circle" "2004.2891,888.2397" "0.5")
(command "_circle" "2001.9371,885.8876" "0.5")
(command "_layer" "set" "nitride" "")
(command "_block" "blkcoupler6" "1920,900" coupler6 "")
(command "_insert" "blkcoupler6" "1920,900" "1" "1" "0")
(command "_insert" "blkcoupler6" "1920,900" "1" "1" "180")
(command "_block" "blksinglenanobeam6" "1920,900" singlenanobeam6 "")
(command "_insert" "blksinglenanobeam6" "1920,900" "1" "1" "0")
(command "_insert" "blksinglenanobeam6" "1920,900" "1" "1" "180")
(command "_block" "blkanglednodearray6" "1920,900" anglednodearray6 "")
(command "_insert" "blkanglednodearray6" "1920,900" "1" "1" "0")
(command "_insert" "blkanglednodearray6" "1920,900" "1" "1" "180")
(command "_block" "blkcooledsinglenanobeam6" "1920,900" cooledsinglenanobeam6 "")
(command "_insert" "blkcooledsinglenanobeam6" "1920,900" "1" "1" "0")
(command "_insert" "blkcooledsinglenanobeam6" "1920,900" "1" "1" "180")
(command "_block" "blkyjunction6" "1920,900" yjunction6 "")
(command "_insert" "blkyjunction6" "1920,900" "1" "1" "0")
(command "_insert" "blkyjunction6" "1920,900" "1" "1" "180")
; DRAWING BULGING VEE GROOVE
(command "_layer" "set" "vgroove" "")
(setq coords (list 
(list 1845.415 -605) 
(list 1845.415 0) 
(list 1845.415 0) 
(list 1845.415 1800) 
(list 1845.415 1800) 
(list 1845.415 2405) 
(list 1994.585 2405) 
(list 1994.585 1800) 
(list 1994.585 1800) 
(list 1994.585 0) 
(list 1994.585 0) 
(list 1994.585 -605)))
(apply 'command (append '("pline") coords '("c")))
(command "._fillet" "radius" "0" "._fillet" "P" (entlast))
(command "_layer" "set" "window" "")
(command "_rectangle" "1845.415,-1935" "1994.585,-600")
(command "_rectangle" "1845.415,2400" "1994.585,5300")
(command "_layer" "set" "grid" "")
(command "_rectangle" "1846.415,-1934" "1869.9433,-1909.2133")
(command "_array" "last" "" "R" "75" "3" "25.7867" "24.5283")
(command "_rectangle" "1921,-1934" "1944.5283,-1909.2133")
(command "_array" "last" "" "R" "75" "3" "25.7867" "24.5283")
(command "_rectangle" "1846.415,1" "1869.9433,25.7")
(command "_array" "last" "" "R" "70" "3" "25.7" "24.5283")
(command "_rectangle" "1921,1" "1944.5283,25.7")
(command "_array" "last" "" "R" "70" "3" "25.7" "24.5283")
(command "_rectangle" "1846.415,1801" "1869.9433,1825.9185")
(command "_array" "last" "" "R" "135" "3" "25.9185" "24.5283")
(command "_rectangle" "1921,1801" "1944.5283,1825.9185")
(command "_array" "last" "" "R" "135" "3" "25.9185" "24.5283")
(command "_layer" "set" "vgrooveFDA" "")
(command "_rectangle" "1994.585,-2233" "1845.415,-1933")
(command "_layer" "set" "nitride" "")
(command "_layer" "set" "holes" "")
(command "_circle" "1997.085,331.5" "0.5")
(command "_array" "last" "" "R" "379" "1" "3" "2.5")
(command "_circle" "1842.915,331.5" "0.5")
(command "_array" "last" "" "R" "379" "1" "3" "-2.5")
(command "_layer" "set" "nitride" "")
(command "_layer" "set" "window" "")
(command "_layer" "set" "window" "")
(command "_rectangle" "1999.585,0" "2160.415,1800")
(command "._fillet" "radius" "20" "._fillet" "P" (entlast))
(command "_layer" "set" "grid" "")
(command "_rectangle" "2000.585,1" "2022.4179,25.7")
(command "_array" "last" "" "R" "70" "7" "25.7" "22.8329")
(command "_layer" "set" "nitride" "")
; DRAWING REGION LAYER
(command "_layer" "set" "regionLayer6" "")
(command "_rectangle" "1840,-460" "2000,2260")
(command "_layer" "set" "nitride" "")
(setq coupler6 nil)
(setq singlenanobeam6 nil)
(setq anglednodearray6 nil)
(setq cooledsinglenanobeam6 nil)
(setq yjunction6 nil)
; DEVICE #7
(command "_layer" "set" "window" "")
(command "_circle" "2152.915,-415" "5")
(command "_circle" "2152.915,-402.5" "5")
(command "_circle" "2152.915,-390" "5")
(command "_circle" "2152.915,-377.5" "5")
(command "_circle" "2140.415,-415" "5")
(command "_circle" "2140.415,-402.5" "5")
(command "_circle" "2140.415,-390" "5")
(command "_layer" "set" "nitride" "")
(setq currobj nil)
(setq currobj (ssadd))
; DRAWING COUPLER
(setq coords (list 
(list 2240.0615 -415) 
(list 2240.0615 -413) 
(list 2313.585 -413) 
(list 2313.585 -413) 
(list 2313.9677 -413.0761) 
(list 2314.2921 -413.2929) 
(list 2314.5089 -413.6173) 
(list 2314.585 -414) 
(list 2314.585 -411.8) 
(list 2314.585 -411.8) 
(list 2314.5089 -412.1827) 
(list 2314.2921 -412.5071) 
(list 2313.9677 -412.7239) 
(list 2313.585 -412.8) 
(list 2240.0615 -412.8) 
(list 2240.0615 -410.8) 
(list 2239.9385 -410.8) 
(list 2239.9385 -412.8) 
(list 2166.415 -412.8) 
(list 2166.0323 -412.7239) 
(list 2165.7079 -412.5071) 
(list 2165.4911 -412.1827) 
(list 2165.415 -411.8) 
(list 2165.415 -411.8) 
(list 2165.415 -414) 
(list 2165.4911 -413.6173) 
(list 2165.7079 -413.2929) 
(list 2166.0323 -413.0761) 
(list 2166.415 -413) 
(list 2166.415 -413) 
(list 2239.9385 -413) 
(list 2239.9385 -415)))
(apply 'command (append '("pline") coords '("c")))
(setq currobj (ssadd (entlast) currobj))
(command "._fillet" "radius" "0.3" "._fillet" "P" (entlast))
(command "_layer" "set" "holes" "")
(command "_circle" "2240,-412.9" "0.113")
(setq currobj (ssadd (entlast) currobj))
(command "_layer" "set" "nitride" "")
(command "_layer" "set" "text" "")
(command "_circle" "2239.2,-415" "0.075")
(command "_circle" "2239.2,-414.7" "0.075")
(command "_circle" "2239.2,-414.4" "0.075")
(command "_circle" "2238.9,-415" "0.075")
(command "_circle" "2238.9,-414.7" "0.075")
(command "_circle" "2238.9,-414.4" "0.075")
(command "_circle" "2238.6,-415" "0.075")
(command "_circle" "2238.6,-414.7" "0.075")
(command "_circle" "2238.6,-414.4" "0.075")
(command "_layer" "set" "nitride" "")
(command "_layer" "set" "prebias" "")
(command "_rectangle" "2165.415,-414" "2314.585,-411.8")
(setq currobj (ssadd (entlast) currobj))
(command "_rectangle" "2239.9385,-415" "2240.0615,-410.8")
(setq currobj (ssadd (entlast) currobj))
(command "_layer" "set" "nitride" "")
(setq coupler7 currobj)
(setq currobj nil)
(setq currobj (ssadd))
; DRAWING SINGLE NANOBEAM
(setq coords (list 
(list 2240.0615 -410.8) 
(list 2240.0615 -409.1417) 
(list 2240.0615 -407.4833) 
(list 2240.0615 -405.825) 
(list 2240.0615 -404.1667) 
(list 2240.0615 -402.5083) 
(list 2240.0615 -400.85) 
(list 2240.0615 -399.1917) 
(list 2240.0615 -397.5333) 
(list 2240.0616 -395.875) 
(list 2240.0616 -394.2167) 
(list 2240.0616 -392.5583) 
(list 2240.0616 -390.9) 
(list 2240.0617 -389.2417) 
(list 2240.0617 -387.5833) 
(list 2240.0617 -385.925) 
(list 2240.0618 -384.2667) 
(list 2240.0619 -382.6083) 
(list 2240.0619 -380.95) 
(list 2240.062 -379.2917) 
(list 2240.0621 -377.6333) 
(list 2240.0622 -375.975) 
(list 2240.0623 -374.3167) 
(list 2240.0624 -372.6583) 
(list 2240.0625 -371) 
(list 2240.0626 -369.3417) 
(list 2240.0628 -367.6833) 
(list 2240.0629 -366.025) 
(list 2240.0631 -364.3667) 
(list 2240.0632 -362.7083) 
(list 2240.0634 -361.05) 
(list 2240.0636 -359.3917) 
(list 2240.0638 -357.7333) 
(list 2240.0641 -356.075) 
(list 2240.0643 -354.4167) 
(list 2240.0646 -352.7583) 
(list 2240.0648 -351.1) 
(list 2240.0651 -349.4417) 
(list 2240.0654 -347.7833) 
(list 2240.0657 -346.125) 
(list 2240.0661 -344.4667) 
(list 2240.0664 -342.8083) 
(list 2240.0668 -341.15) 
(list 2240.0672 -339.4917) 
(list 2240.0676 -337.8333) 
(list 2240.068 -336.175) 
(list 2240.0685 -334.5167) 
(list 2240.0689 -332.8583) 
(list 2240.0694 -331.2) 
(list 2240.0699 -329.5417) 
(list 2240.0704 -327.8833) 
(list 2240.071 -326.225) 
(list 2240.0715 -324.5667) 
(list 2240.0721 -322.9083) 
(list 2240.0728 -321.25) 
(list 2240.0734 -319.5917) 
(list 2240.0741 -317.9333) 
(list 2240.0747 -316.275) 
(list 2240.0754 -314.6167) 
(list 2240.0762 -312.9583) 
(list 2240.0769 -311.3) 
(list 2240.0777 -309.6417) 
(list 2240.0785 -307.9833) 
(list 2240.0794 -306.325) 
(list 2240.0802 -304.6667) 
(list 2240.0811 -303.0083) 
(list 2240.082 -301.35) 
(list 2240.083 -299.6917) 
(list 2240.084 -298.0333) 
(list 2240.085 -296.375) 
(list 2240.086 -294.7167) 
(list 2240.0871 -293.0583) 
(list 2240.0882 -291.4) 
(list 2240.0893 -289.7417) 
(list 2240.0905 -288.0833) 
(list 2240.0917 -286.425) 
(list 2240.0929 -284.7667) 
(list 2240.0941 -283.1083) 
(list 2240.0954 -281.45) 
(list 2240.0967 -279.7917) 
(list 2240.0981 -278.1333) 
(list 2240.0995 -276.475) 
(list 2240.1009 -274.8167) 
(list 2240.1024 -273.1583) 
(list 2240.1039 -271.5) 
(list 2240.1054 -269.8417) 
(list 2240.107 -268.1833) 
(list 2240.1086 -266.525) 
(list 2240.1102 -264.8667) 
(list 2240.1119 -263.2083) 
(list 2240.1136 -261.55) 
(list 2240.1154 -259.8917) 
(list 2240.1172 -258.2333) 
(list 2240.119 -256.575) 
(list 2240.1209 -254.9167) 
(list 2240.1228 -253.2583) 
(list 2240.1247 -251.6) 
(list 2240.1267 -249.9417) 
(list 2240.1288 -248.2833) 
(list 2240.1308 -246.625) 
(list 2240.133 -244.9667) 
(list 2240.1351 -243.3083) 
(list 2240.1373 -241.65) 
(list 2240.1396 -239.9917) 
(list 2240.1419 -238.3333) 
(list 2240.1442 -236.675) 
(list 2240.1466 -235.0167) 
(list 2240.1491 -233.3583) 
(list 2240.1515 -231.7) 
(list 2240.1541 -230.0417) 
(list 2240.1566 -228.3833) 
(list 2240.1592 -226.725) 
(list 2240.1619 -225.0667) 
(list 2240.1646 -223.4083) 
(list 2240.1674 -221.75) 
(list 2240.1702 -220.0917) 
(list 2240.1731 -218.4333) 
(list 2240.176 -216.775) 
(list 2240.1789 -215.1167) 
(list 2240.1819 -213.4583) 
(list 2240.185 -211.8) 
(list 2239.815 -211.8) 
(list 2239.8181 -213.4583) 
(list 2239.8211 -215.1167) 
(list 2239.824 -216.775) 
(list 2239.8269 -218.4333) 
(list 2239.8298 -220.0917) 
(list 2239.8326 -221.75) 
(list 2239.8354 -223.4083) 
(list 2239.8381 -225.0667) 
(list 2239.8408 -226.725) 
(list 2239.8434 -228.3833) 
(list 2239.8459 -230.0417) 
(list 2239.8485 -231.7) 
(list 2239.8509 -233.3583) 
(list 2239.8534 -235.0167) 
(list 2239.8558 -236.675) 
(list 2239.8581 -238.3333) 
(list 2239.8604 -239.9917) 
(list 2239.8627 -241.65) 
(list 2239.8649 -243.3083) 
(list 2239.867 -244.9667) 
(list 2239.8692 -246.625) 
(list 2239.8712 -248.2833) 
(list 2239.8733 -249.9417) 
(list 2239.8753 -251.6) 
(list 2239.8772 -253.2583) 
(list 2239.8791 -254.9167) 
(list 2239.881 -256.575) 
(list 2239.8828 -258.2333) 
(list 2239.8846 -259.8917) 
(list 2239.8864 -261.55) 
(list 2239.8881 -263.2083) 
(list 2239.8898 -264.8667) 
(list 2239.8914 -266.525) 
(list 2239.893 -268.1833) 
(list 2239.8946 -269.8417) 
(list 2239.8961 -271.5) 
(list 2239.8976 -273.1583) 
(list 2239.8991 -274.8167) 
(list 2239.9005 -276.475) 
(list 2239.9019 -278.1333) 
(list 2239.9033 -279.7917) 
(list 2239.9046 -281.45) 
(list 2239.9059 -283.1083) 
(list 2239.9071 -284.7667) 
(list 2239.9083 -286.425) 
(list 2239.9095 -288.0833) 
(list 2239.9107 -289.7417) 
(list 2239.9118 -291.4) 
(list 2239.9129 -293.0583) 
(list 2239.914 -294.7167) 
(list 2239.915 -296.375) 
(list 2239.916 -298.0333) 
(list 2239.917 -299.6917) 
(list 2239.918 -301.35) 
(list 2239.9189 -303.0083) 
(list 2239.9198 -304.6667) 
(list 2239.9206 -306.325) 
(list 2239.9215 -307.9833) 
(list 2239.9223 -309.6417) 
(list 2239.9231 -311.3) 
(list 2239.9238 -312.9583) 
(list 2239.9246 -314.6167) 
(list 2239.9253 -316.275) 
(list 2239.9259 -317.9333) 
(list 2239.9266 -319.5917) 
(list 2239.9272 -321.25) 
(list 2239.9279 -322.9083) 
(list 2239.9285 -324.5667) 
(list 2239.929 -326.225) 
(list 2239.9296 -327.8833) 
(list 2239.9301 -329.5417) 
(list 2239.9306 -331.2) 
(list 2239.9311 -332.8583) 
(list 2239.9315 -334.5167) 
(list 2239.932 -336.175) 
(list 2239.9324 -337.8333) 
(list 2239.9328 -339.4917) 
(list 2239.9332 -341.15) 
(list 2239.9336 -342.8083) 
(list 2239.9339 -344.4667) 
(list 2239.9343 -346.125) 
(list 2239.9346 -347.7833) 
(list 2239.9349 -349.4417) 
(list 2239.9352 -351.1) 
(list 2239.9354 -352.7583) 
(list 2239.9357 -354.4167) 
(list 2239.9359 -356.075) 
(list 2239.9362 -357.7333) 
(list 2239.9364 -359.3917) 
(list 2239.9366 -361.05) 
(list 2239.9368 -362.7083) 
(list 2239.9369 -364.3667) 
(list 2239.9371 -366.025) 
(list 2239.9372 -367.6833) 
(list 2239.9374 -369.3417) 
(list 2239.9375 -371) 
(list 2239.9376 -372.6583) 
(list 2239.9377 -374.3167) 
(list 2239.9378 -375.975) 
(list 2239.9379 -377.6333) 
(list 2239.938 -379.2917) 
(list 2239.9381 -380.95) 
(list 2239.9381 -382.6083) 
(list 2239.9382 -384.2667) 
(list 2239.9383 -385.925) 
(list 2239.9383 -387.5833) 
(list 2239.9383 -389.2417) 
(list 2239.9384 -390.9) 
(list 2239.9384 -392.5583) 
(list 2239.9384 -394.2167) 
(list 2239.9384 -395.875) 
(list 2239.9385 -397.5333) 
(list 2239.9385 -399.1917) 
(list 2239.9385 -400.85) 
(list 2239.9385 -402.5083) 
(list 2239.9385 -404.1667) 
(list 2239.9385 -405.825) 
(list 2239.9385 -407.4833) 
(list 2239.9385 -409.1417) 
(list 2239.9385 -410.8)))
(apply 'command (append '("pline") coords '("c")))
(setq currobj (ssadd (entlast) currobj))
(command "_layer" "set" "prebias" "")
(command "_rectangle" "2239.815,-410.8" "2240.185,-211.8")
(setq currobj (ssadd (entlast) currobj))
(command "_layer" "set" "nitride" "")
(setq singlenanobeam7 currobj)
(setq currobj nil)
(setq currobj (ssadd))
; DRAWING NODE ARRAY
(setq coords (list 
(list 2240.185 -211.8) 
(list 2240.5625 -201.8) 
(list 2240.5625 -201.8) 
(list 2240.5625 -200.8) 
(list 2314.585 -212.6864) 
(list 2314.585 -207.7434) 
(list 2240.5625 -197.357) 
(list 2240.5625 -196.357) 
(list 2240.5625 -196.357) 
(list 2240.2625 -186.357) 
(list 2239.7375 -186.357) 
(list 2239.4375 -196.357) 
(list 2239.4375 -196.357) 
(list 2239.4375 -197.357) 
(list 2165.415 -207.7434) 
(list 2165.415 -212.6864) 
(list 2239.4375 -200.8) 
(list 2239.4375 -201.8) 
(list 2239.4375 -201.8) 
(list 2239.815 -211.8)))
(apply 'command (append '("pline") coords '("c")))
(setq currobj (ssadd (entlast) currobj))
(command "_layer" "set" "prebias" "")
(setq coords (list 
(list 2239.4375 -212.6864) 
(list 2239.4375 -200.8) 
(list 2165.415 -212.6864) 
(list 2165.415 -207.7434) 
(list 2239.4375 -197.357) 
(list 2239.4375 -186.357) 
(list 2240.5625 -186.357) 
(list 2240.5625 -197.357) 
(list 2314.585 -207.7434) 
(list 2314.585 -212.6864) 
(list 2240.5625 -200.8) 
(list 2240.5625 -212.6864)))
(apply 'command (append '("pline") coords '("c")))
(setq currobj (ssadd (entlast) currobj))
(command "_layer" "set" "nitride" "")
(command "_layer" "set" "fda1" "")
(setq coords (list 
(list 2240.5625 -200.657) 
(list 2314.585 -212.5434) 
(list 2314.585 -212.3664) 
(list 2240.5625 -200.58)))
(apply 'command (append '("pline") coords '("c")))
(setq currobj (ssadd (entlast) currobj))
(setq coords (list 
(list 2240.5625 -200.437) 
(list 2314.585 -212.2234) 
(list 2314.585 -212.0464) 
(list 2240.5625 -200.36)))
(apply 'command (append '("pline") coords '("c")))
(setq currobj (ssadd (entlast) currobj))
(setq coords (list 
(list 2240.5625 -200.217) 
(list 2314.585 -211.9034) 
(list 2314.585 -211.7264) 
(list 2240.5625 -200.14)))
(apply 'command (append '("pline") coords '("c")))
(setq currobj (ssadd (entlast) currobj))
(setq coords (list 
(list 2240.5625 -199.997) 
(list 2314.585 -211.5834) 
(list 2314.585 -211.4064) 
(list 2240.5625 -199.92)))
(apply 'command (append '("pline") coords '("c")))
(setq currobj (ssadd (entlast) currobj))
(setq coords (list 
(list 2240.5625 -199.777) 
(list 2314.585 -211.2634) 
(list 2314.585 -211.0864) 
(list 2240.5625 -199.7)))
(apply 'command (append '("pline") coords '("c")))
(setq currobj (ssadd (entlast) currobj))
(setq coords (list 
(list 2240.5625 -199.557) 
(list 2314.585 -210.9434) 
(list 2314.585 -210.7664) 
(list 2240.5625 -199.48)))
(apply 'command (append '("pline") coords '("c")))
(setq currobj (ssadd (entlast) currobj))
(setq coords (list 
(list 2240.5625 -199.337) 
(list 2314.585 -210.6234) 
(list 2314.585 -210.4464) 
(list 2240.5625 -199.26)))
(apply 'command (append '("pline") coords '("c")))
(setq currobj (ssadd (entlast) currobj))
(setq coords (list 
(list 2240.5625 -199.117) 
(list 2314.585 -210.3034) 
(list 2314.585 -210.1264) 
(list 2240.5625 -199.04)))
(apply 'command (append '("pline") coords '("c")))
(setq currobj (ssadd (entlast) currobj))
(setq coords (list 
(list 2240.5625 -198.897) 
(list 2314.585 -209.9834) 
(list 2314.585 -209.8064) 
(list 2240.5625 -198.82)))
(apply 'command (append '("pline") coords '("c")))
(setq currobj (ssadd (entlast) currobj))
(setq coords (list 
(list 2240.5625 -198.677) 
(list 2314.585 -209.6634) 
(list 2314.585 -209.4864) 
(list 2240.5625 -198.6)))
(apply 'command (append '("pline") coords '("c")))
(setq currobj (ssadd (entlast) currobj))
(setq coords (list 
(list 2240.5625 -198.457) 
(list 2314.585 -209.3434) 
(list 2314.585 -209.1664) 
(list 2240.5625 -198.38)))
(apply 'command (append '("pline") coords '("c")))
(setq currobj (ssadd (entlast) currobj))
(setq coords (list 
(list 2240.5625 -198.237) 
(list 2314.585 -209.0234) 
(list 2314.585 -208.8464) 
(list 2240.5625 -198.16)))
(apply 'command (append '("pline") coords '("c")))
(setq currobj (ssadd (entlast) currobj))
(setq coords (list 
(list 2240.5625 -198.017) 
(list 2314.585 -208.7034) 
(list 2314.585 -208.5264) 
(list 2240.5625 -197.94)))
(apply 'command (append '("pline") coords '("c")))
(setq currobj (ssadd (entlast) currobj))
(setq coords (list 
(list 2240.5625 -197.797) 
(list 2314.585 -208.3834) 
(list 2314.585 -208.2064) 
(list 2240.5625 -197.72)))
(apply 'command (append '("pline") coords '("c")))
(setq currobj (ssadd (entlast) currobj))
(setq coords (list 
(list 2240.5625 -197.577) 
(list 2314.585 -208.0634) 
(list 2314.585 -207.8864) 
(list 2240.5625 -197.5)))
(apply 'command (append '("pline") coords '("c")))
(setq currobj (ssadd (entlast) currobj))
(setq coords (list 
(list 2239.4375 -197.5) 
(list 2165.415 -207.8864) 
(list 2165.415 -208.0634) 
(list 2239.4375 -197.577)))
(apply 'command (append '("pline") coords '("c")))
(setq currobj (ssadd (entlast) currobj))
(setq coords (list 
(list 2239.4375 -197.72) 
(list 2165.415 -208.2064) 
(list 2165.415 -208.3834) 
(list 2239.4375 -197.797)))
(apply 'command (append '("pline") coords '("c")))
(setq currobj (ssadd (entlast) currobj))
(setq coords (list 
(list 2239.4375 -197.94) 
(list 2165.415 -208.5264) 
(list 2165.415 -208.7034) 
(list 2239.4375 -198.017)))
(apply 'command (append '("pline") coords '("c")))
(setq currobj (ssadd (entlast) currobj))
(setq coords (list 
(list 2239.4375 -198.16) 
(list 2165.415 -208.8464) 
(list 2165.415 -209.0234) 
(list 2239.4375 -198.237)))
(apply 'command (append '("pline") coords '("c")))
(setq currobj (ssadd (entlast) currobj))
(setq coords (list 
(list 2239.4375 -198.38) 
(list 2165.415 -209.1664) 
(list 2165.415 -209.3434) 
(list 2239.4375 -198.457)))
(apply 'command (append '("pline") coords '("c")))
(setq currobj (ssadd (entlast) currobj))
(setq coords (list 
(list 2239.4375 -198.6) 
(list 2165.415 -209.4864) 
(list 2165.415 -209.6634) 
(list 2239.4375 -198.677)))
(apply 'command (append '("pline") coords '("c")))
(setq currobj (ssadd (entlast) currobj))
(setq coords (list 
(list 2239.4375 -198.82) 
(list 2165.415 -209.8064) 
(list 2165.415 -209.9834) 
(list 2239.4375 -198.897)))
(apply 'command (append '("pline") coords '("c")))
(setq currobj (ssadd (entlast) currobj))
(setq coords (list 
(list 2239.4375 -199.04) 
(list 2165.415 -210.1264) 
(list 2165.415 -210.3034) 
(list 2239.4375 -199.117)))
(apply 'command (append '("pline") coords '("c")))
(setq currobj (ssadd (entlast) currobj))
(setq coords (list 
(list 2239.4375 -199.26) 
(list 2165.415 -210.4464) 
(list 2165.415 -210.6234) 
(list 2239.4375 -199.337)))
(apply 'command (append '("pline") coords '("c")))
(setq currobj (ssadd (entlast) currobj))
(setq coords (list 
(list 2239.4375 -199.48) 
(list 2165.415 -210.7664) 
(list 2165.415 -210.9434) 
(list 2239.4375 -199.557)))
(apply 'command (append '("pline") coords '("c")))
(setq currobj (ssadd (entlast) currobj))
(setq coords (list 
(list 2239.4375 -199.7) 
(list 2165.415 -211.0864) 
(list 2165.415 -211.2634) 
(list 2239.4375 -199.777)))
(apply 'command (append '("pline") coords '("c")))
(setq currobj (ssadd (entlast) currobj))
(setq coords (list 
(list 2239.4375 -199.92) 
(list 2165.415 -211.4064) 
(list 2165.415 -211.5834) 
(list 2239.4375 -199.997)))
(apply 'command (append '("pline") coords '("c")))
(setq currobj (ssadd (entlast) currobj))
(setq coords (list 
(list 2239.4375 -200.14) 
(list 2165.415 -211.7264) 
(list 2165.415 -211.9034) 
(list 2239.4375 -200.217)))
(apply 'command (append '("pline") coords '("c")))
(setq currobj (ssadd (entlast) currobj))
(setq coords (list 
(list 2239.4375 -200.36) 
(list 2165.415 -212.0464) 
(list 2165.415 -212.2234) 
(list 2239.4375 -200.437)))
(apply 'command (append '("pline") coords '("c")))
(setq currobj (ssadd (entlast) currobj))
(setq coords (list 
(list 2239.4375 -200.58) 
(list 2165.415 -212.3664) 
(list 2165.415 -212.5434) 
(list 2239.4375 -200.657)))
(apply 'command (append '("pline") coords '("c")))
(setq currobj (ssadd (entlast) currobj))
(command "_layer" "set" "nitride" "")
(command "_layer" "set" "text" "")
(command "_circle" "2238.985,-211.8" "0.075")
(command "_circle" "2238.985,-211.5" "0.075")
(command "_circle" "2238.985,-211.2" "0.075")
(command "_circle" "2238.985,-210.9" "0.075")
(command "_circle" "2238.985,-210.6" "0.075")
(command "_circle" "2238.685,-211.8" "0.075")
(command "_circle" "2238.685,-211.5" "0.075")
(command "_circle" "2238.685,-211.2" "0.075")
(command "_circle" "2238.685,-210.9" "0.075")
(command "_circle" "2238.685,-210.6" "0.075")
(command "_circle" "2238.385,-211.8" "0.075")
(command "_circle" "2238.385,-211.5" "0.075")
(command "_circle" "2238.385,-211.2" "0.075")
(command "_circle" "2238.385,-210.9" "0.075")
(command "_circle" "2238.385,-210.6" "0.075")
(command "_circle" "2238.085,-211.8" "0.075")
(command "_circle" "2238.085,-211.5" "0.075")
(command "_circle" "2238.085,-211.2" "0.075")
(command "_circle" "2238.085,-210.9" "0.075")
(command "_circle" "2238.085,-210.6" "0.075")
(command "_circle" "2237.785,-211.8" "0.075")
(command "_circle" "2237.785,-211.5" "0.075")
(command "_circle" "2237.785,-211.2" "0.075")
(command "_circle" "2237.785,-210.9" "0.075")
(command "_circle" "2237.785,-210.6" "0.075")
(command "_layer" "set" "nitride" "")
(setq anglednodearray7 currobj)
(setq currobj nil)
(setq currobj (ssadd))
; DRAWING COOLED SINGLE NANOBEAM
(setq coords (list 
(list 2240.2625 -186.357) 
(list 2240.2625 -181.357) 
(list 2239.7375 -181.357) 
(list 2239.7375 -186.357)))
(apply 'command (append '("pline") coords '("c")))
(setq currobj (ssadd (entlast) currobj))
(command "_layer" "set" "prebias" "")
(command "_rectangle" "2239.7375,-186.357" "2240.2625,-181.357")
(setq currobj (ssadd (entlast) currobj))
(command "_layer" "set" "nitride" "")
(setq coords (list 
(list 2240.2625 -181.357) 
(list 2240.5625 -171.357) 
(list 2240.5625 -171.357) 
(list 2240.5625 -170.357) 
(list 2314.585 -171.107) 
(list 2314.585 -166.164) 
(list 2240.5625 -166.914) 
(list 2240.5625 -165.914) 
(list 2240.5625 -165.914) 
(list 2240.2625 -155.914) 
(list 2239.7375 -155.914) 
(list 2239.4375 -165.914) 
(list 2239.4375 -165.914) 
(list 2239.4375 -166.914) 
(list 2165.415 -166.164) 
(list 2165.415 -171.107) 
(list 2239.4375 -170.357) 
(list 2239.4375 -171.357) 
(list 2239.4375 -171.357) 
(list 2239.7375 -181.357)))
(apply 'command (append '("pline") coords '("c")))
(setq currobj (ssadd (entlast) currobj))
(command "_layer" "set" "prebias" "")
(setq coords (list 
(list 2239.4375 -181.357) 
(list 2239.4375 -170.357) 
(list 2165.415 -171.107) 
(list 2165.415 -166.164) 
(list 2239.4375 -166.914) 
(list 2239.4375 -155.914) 
(list 2240.5625 -155.914) 
(list 2240.5625 -166.914) 
(list 2314.585 -166.164) 
(list 2314.585 -171.107) 
(list 2240.5625 -170.357) 
(list 2240.5625 -181.357)))
(apply 'command (append '("pline") coords '("c")))
(setq currobj (ssadd (entlast) currobj))
(command "_layer" "set" "nitride" "")
(command "_layer" "set" "fda1" "")
(setq coords (list 
(list 2240.5625 -170.214) 
(list 2314.585 -170.964) 
(list 2314.585 -170.787) 
(list 2240.5625 -170.137)))
(apply 'command (append '("pline") coords '("c")))
(setq currobj (ssadd (entlast) currobj))
(setq coords (list 
(list 2240.5625 -169.994) 
(list 2314.585 -170.644) 
(list 2314.585 -170.467) 
(list 2240.5625 -169.917)))
(apply 'command (append '("pline") coords '("c")))
(setq currobj (ssadd (entlast) currobj))
(setq coords (list 
(list 2240.5625 -169.774) 
(list 2314.585 -170.324) 
(list 2314.585 -170.147) 
(list 2240.5625 -169.697)))
(apply 'command (append '("pline") coords '("c")))
(setq currobj (ssadd (entlast) currobj))
(setq coords (list 
(list 2240.5625 -169.554) 
(list 2314.585 -170.004) 
(list 2314.585 -169.827) 
(list 2240.5625 -169.477)))
(apply 'command (append '("pline") coords '("c")))
(setq currobj (ssadd (entlast) currobj))
(setq coords (list 
(list 2240.5625 -169.334) 
(list 2314.585 -169.684) 
(list 2314.585 -169.507) 
(list 2240.5625 -169.257)))
(apply 'command (append '("pline") coords '("c")))
(setq currobj (ssadd (entlast) currobj))
(setq coords (list 
(list 2240.5625 -169.114) 
(list 2314.585 -169.364) 
(list 2314.585 -169.187) 
(list 2240.5625 -169.037)))
(apply 'command (append '("pline") coords '("c")))
(setq currobj (ssadd (entlast) currobj))
(setq coords (list 
(list 2240.5625 -168.894) 
(list 2314.585 -169.044) 
(list 2314.585 -168.867) 
(list 2240.5625 -168.817)))
(apply 'command (append '("pline") coords '("c")))
(setq currobj (ssadd (entlast) currobj))
(setq coords (list 
(list 2240.5625 -168.674) 
(list 2314.585 -168.724) 
(list 2314.585 -168.547) 
(list 2240.5625 -168.597)))
(apply 'command (append '("pline") coords '("c")))
(setq currobj (ssadd (entlast) currobj))
(setq coords (list 
(list 2240.5625 -168.454) 
(list 2314.585 -168.404) 
(list 2314.585 -168.227) 
(list 2240.5625 -168.377)))
(apply 'command (append '("pline") coords '("c")))
(setq currobj (ssadd (entlast) currobj))
(setq coords (list 
(list 2240.5625 -168.234) 
(list 2314.585 -168.084) 
(list 2314.585 -167.907) 
(list 2240.5625 -168.157)))
(apply 'command (append '("pline") coords '("c")))
(setq currobj (ssadd (entlast) currobj))
(setq coords (list 
(list 2240.5625 -168.014) 
(list 2314.585 -167.764) 
(list 2314.585 -167.587) 
(list 2240.5625 -167.937)))
(apply 'command (append '("pline") coords '("c")))
(setq currobj (ssadd (entlast) currobj))
(setq coords (list 
(list 2240.5625 -167.794) 
(list 2314.585 -167.444) 
(list 2314.585 -167.267) 
(list 2240.5625 -167.717)))
(apply 'command (append '("pline") coords '("c")))
(setq currobj (ssadd (entlast) currobj))
(setq coords (list 
(list 2240.5625 -167.574) 
(list 2314.585 -167.124) 
(list 2314.585 -166.947) 
(list 2240.5625 -167.497)))
(apply 'command (append '("pline") coords '("c")))
(setq currobj (ssadd (entlast) currobj))
(setq coords (list 
(list 2240.5625 -167.354) 
(list 2314.585 -166.804) 
(list 2314.585 -166.627) 
(list 2240.5625 -167.277)))
(apply 'command (append '("pline") coords '("c")))
(setq currobj (ssadd (entlast) currobj))
(setq coords (list 
(list 2240.5625 -167.134) 
(list 2314.585 -166.484) 
(list 2314.585 -166.307) 
(list 2240.5625 -167.057)))
(apply 'command (append '("pline") coords '("c")))
(setq currobj (ssadd (entlast) currobj))
(setq coords (list 
(list 2239.4375 -167.057) 
(list 2165.415 -166.307) 
(list 2165.415 -166.484) 
(list 2239.4375 -167.134)))
(apply 'command (append '("pline") coords '("c")))
(setq currobj (ssadd (entlast) currobj))
(setq coords (list 
(list 2239.4375 -167.277) 
(list 2165.415 -166.627) 
(list 2165.415 -166.804) 
(list 2239.4375 -167.354)))
(apply 'command (append '("pline") coords '("c")))
(setq currobj (ssadd (entlast) currobj))
(setq coords (list 
(list 2239.4375 -167.497) 
(list 2165.415 -166.947) 
(list 2165.415 -167.124) 
(list 2239.4375 -167.574)))
(apply 'command (append '("pline") coords '("c")))
(setq currobj (ssadd (entlast) currobj))
(setq coords (list 
(list 2239.4375 -167.717) 
(list 2165.415 -167.267) 
(list 2165.415 -167.444) 
(list 2239.4375 -167.794)))
(apply 'command (append '("pline") coords '("c")))
(setq currobj (ssadd (entlast) currobj))
(setq coords (list 
(list 2239.4375 -167.937) 
(list 2165.415 -167.587) 
(list 2165.415 -167.764) 
(list 2239.4375 -168.014)))
(apply 'command (append '("pline") coords '("c")))
(setq currobj (ssadd (entlast) currobj))
(setq coords (list 
(list 2239.4375 -168.157) 
(list 2165.415 -167.907) 
(list 2165.415 -168.084) 
(list 2239.4375 -168.234)))
(apply 'command (append '("pline") coords '("c")))
(setq currobj (ssadd (entlast) currobj))
(setq coords (list 
(list 2239.4375 -168.377) 
(list 2165.415 -168.227) 
(list 2165.415 -168.404) 
(list 2239.4375 -168.454)))
(apply 'command (append '("pline") coords '("c")))
(setq currobj (ssadd (entlast) currobj))
(setq coords (list 
(list 2239.4375 -168.597) 
(list 2165.415 -168.547) 
(list 2165.415 -168.724) 
(list 2239.4375 -168.674)))
(apply 'command (append '("pline") coords '("c")))
(setq currobj (ssadd (entlast) currobj))
(setq coords (list 
(list 2239.4375 -168.817) 
(list 2165.415 -168.867) 
(list 2165.415 -169.044) 
(list 2239.4375 -168.894)))
(apply 'command (append '("pline") coords '("c")))
(setq currobj (ssadd (entlast) currobj))
(setq coords (list 
(list 2239.4375 -169.037) 
(list 2165.415 -169.187) 
(list 2165.415 -169.364) 
(list 2239.4375 -169.114)))
(apply 'command (append '("pline") coords '("c")))
(setq currobj (ssadd (entlast) currobj))
(setq coords (list 
(list 2239.4375 -169.257) 
(list 2165.415 -169.507) 
(list 2165.415 -169.684) 
(list 2239.4375 -169.334)))
(apply 'command (append '("pline") coords '("c")))
(setq currobj (ssadd (entlast) currobj))
(setq coords (list 
(list 2239.4375 -169.477) 
(list 2165.415 -169.827) 
(list 2165.415 -170.004) 
(list 2239.4375 -169.554)))
(apply 'command (append '("pline") coords '("c")))
(setq currobj (ssadd (entlast) currobj))
(setq coords (list 
(list 2239.4375 -169.697) 
(list 2165.415 -170.147) 
(list 2165.415 -170.324) 
(list 2239.4375 -169.774)))
(apply 'command (append '("pline") coords '("c")))
(setq currobj (ssadd (entlast) currobj))
(setq coords (list 
(list 2239.4375 -169.917) 
(list 2165.415 -170.467) 
(list 2165.415 -170.644) 
(list 2239.4375 -169.994)))
(apply 'command (append '("pline") coords '("c")))
(setq currobj (ssadd (entlast) currobj))
(setq coords (list 
(list 2239.4375 -170.137) 
(list 2165.415 -170.787) 
(list 2165.415 -170.964) 
(list 2239.4375 -170.214)))
(apply 'command (append '("pline") coords '("c")))
(setq currobj (ssadd (entlast) currobj))
(command "_layer" "set" "nitride" "")
(command "_layer" "set" "text" "")
(command "_circle" "2239.0625,-181.357" "0.075")
(command "_circle" "2239.0625,-181.057" "0.075")
(command "_circle" "2239.0625,-180.757" "0.075")
(command "_circle" "2239.0625,-180.457" "0.075")
(command "_circle" "2239.0625,-180.157" "0.075")
(command "_circle" "2238.7625,-181.357" "0.075")
(command "_circle" "2238.7625,-181.057" "0.075")
(command "_circle" "2238.7625,-180.757" "0.075")
(command "_circle" "2238.7625,-180.457" "0.075")
(command "_circle" "2238.7625,-180.157" "0.075")
(command "_circle" "2238.4625,-181.357" "0.075")
(command "_circle" "2238.4625,-181.057" "0.075")
(command "_circle" "2238.4625,-180.757" "0.075")
(command "_circle" "2238.4625,-180.457" "0.075")
(command "_circle" "2238.4625,-180.157" "0.075")
(command "_circle" "2238.1625,-181.357" "0.075")
(command "_circle" "2238.1625,-181.057" "0.075")
(command "_circle" "2238.1625,-180.757" "0.075")
(command "_circle" "2238.1625,-180.457" "0.075")
(command "_circle" "2238.1625,-180.157" "0.075")
(command "_circle" "2237.8625,-181.357" "0.075")
(command "_circle" "2237.8625,-181.057" "0.075")
(command "_circle" "2237.8625,-180.757" "0.075")
(command "_circle" "2237.8625,-180.457" "0.075")
(command "_circle" "2237.8625,-180.157" "0.075")
(command "_layer" "set" "nitride" "")
(setq coords (list 
(list 2240.2625 -155.914) 
(list 2240.2625 -40.2693) 
(list 2239.7375 -40.2693) 
(list 2239.7375 -155.914)))
(apply 'command (append '("pline") coords '("c")))
(setq currobj (ssadd (entlast) currobj))
(command "_layer" "set" "prebias" "")
(command "_rectangle" "2239.7375,-155.914" "2240.2625,-40.2693")
(setq currobj (ssadd (entlast) currobj))
(command "_layer" "set" "nitride" "")
(setq coords (list 
(list 2240.2625 -40.2693) 
(list 2240.5625 -30.2693) 
(list 2240.5625 -30.2693) 
(list 2240.5625 -29.2693) 
(list 2314.585 -30.0193) 
(list 2314.585 -25.0763) 
(list 2240.5625 -25.8263) 
(list 2240.5625 -24.8263) 
(list 2240.5625 -24.8263) 
(list 2240.2625 -14.8263) 
(list 2239.7375 -14.8263) 
(list 2239.4375 -24.8263) 
(list 2239.4375 -24.8263) 
(list 2239.4375 -25.8263) 
(list 2165.415 -25.0763) 
(list 2165.415 -30.0193) 
(list 2239.4375 -29.2693) 
(list 2239.4375 -30.2693) 
(list 2239.4375 -30.2693) 
(list 2239.7375 -40.2693)))
(apply 'command (append '("pline") coords '("c")))
(setq currobj (ssadd (entlast) currobj))
(command "_layer" "set" "prebias" "")
(setq coords (list 
(list 2239.4375 -40.2693) 
(list 2239.4375 -29.2693) 
(list 2165.415 -30.0193) 
(list 2165.415 -25.0763) 
(list 2239.4375 -25.8263) 
(list 2239.4375 -14.8263) 
(list 2240.5625 -14.8263) 
(list 2240.5625 -25.8263) 
(list 2314.585 -25.0763) 
(list 2314.585 -30.0193) 
(list 2240.5625 -29.2693) 
(list 2240.5625 -40.2693)))
(apply 'command (append '("pline") coords '("c")))
(setq currobj (ssadd (entlast) currobj))
(command "_layer" "set" "nitride" "")
(command "_layer" "set" "fda1" "")
(setq coords (list 
(list 2240.5625 -29.1263) 
(list 2314.585 -29.8763) 
(list 2314.585 -29.6993) 
(list 2240.5625 -29.0493)))
(apply 'command (append '("pline") coords '("c")))
(setq currobj (ssadd (entlast) currobj))
(setq coords (list 
(list 2240.5625 -28.9063) 
(list 2314.585 -29.5563) 
(list 2314.585 -29.3793) 
(list 2240.5625 -28.8293)))
(apply 'command (append '("pline") coords '("c")))
(setq currobj (ssadd (entlast) currobj))
(setq coords (list 
(list 2240.5625 -28.6863) 
(list 2314.585 -29.2363) 
(list 2314.585 -29.0593) 
(list 2240.5625 -28.6093)))
(apply 'command (append '("pline") coords '("c")))
(setq currobj (ssadd (entlast) currobj))
(setq coords (list 
(list 2240.5625 -28.4663) 
(list 2314.585 -28.9163) 
(list 2314.585 -28.7393) 
(list 2240.5625 -28.3893)))
(apply 'command (append '("pline") coords '("c")))
(setq currobj (ssadd (entlast) currobj))
(setq coords (list 
(list 2240.5625 -28.2463) 
(list 2314.585 -28.5963) 
(list 2314.585 -28.4193) 
(list 2240.5625 -28.1693)))
(apply 'command (append '("pline") coords '("c")))
(setq currobj (ssadd (entlast) currobj))
(setq coords (list 
(list 2240.5625 -28.0263) 
(list 2314.585 -28.2763) 
(list 2314.585 -28.0993) 
(list 2240.5625 -27.9493)))
(apply 'command (append '("pline") coords '("c")))
(setq currobj (ssadd (entlast) currobj))
(setq coords (list 
(list 2240.5625 -27.8063) 
(list 2314.585 -27.9563) 
(list 2314.585 -27.7793) 
(list 2240.5625 -27.7293)))
(apply 'command (append '("pline") coords '("c")))
(setq currobj (ssadd (entlast) currobj))
(setq coords (list 
(list 2240.5625 -27.5863) 
(list 2314.585 -27.6363) 
(list 2314.585 -27.4593) 
(list 2240.5625 -27.5093)))
(apply 'command (append '("pline") coords '("c")))
(setq currobj (ssadd (entlast) currobj))
(setq coords (list 
(list 2240.5625 -27.3663) 
(list 2314.585 -27.3163) 
(list 2314.585 -27.1393) 
(list 2240.5625 -27.2893)))
(apply 'command (append '("pline") coords '("c")))
(setq currobj (ssadd (entlast) currobj))
(setq coords (list 
(list 2240.5625 -27.1463) 
(list 2314.585 -26.9963) 
(list 2314.585 -26.8193) 
(list 2240.5625 -27.0693)))
(apply 'command (append '("pline") coords '("c")))
(setq currobj (ssadd (entlast) currobj))
(setq coords (list 
(list 2240.5625 -26.9263) 
(list 2314.585 -26.6763) 
(list 2314.585 -26.4993) 
(list 2240.5625 -26.8493)))
(apply 'command (append '("pline") coords '("c")))
(setq currobj (ssadd (entlast) currobj))
(setq coords (list 
(list 2240.5625 -26.7063) 
(list 2314.585 -26.3563) 
(list 2314.585 -26.1793) 
(list 2240.5625 -26.6293)))
(apply 'command (append '("pline") coords '("c")))
(setq currobj (ssadd (entlast) currobj))
(setq coords (list 
(list 2240.5625 -26.4863) 
(list 2314.585 -26.0363) 
(list 2314.585 -25.8593) 
(list 2240.5625 -26.4093)))
(apply 'command (append '("pline") coords '("c")))
(setq currobj (ssadd (entlast) currobj))
(setq coords (list 
(list 2240.5625 -26.2663) 
(list 2314.585 -25.7163) 
(list 2314.585 -25.5393) 
(list 2240.5625 -26.1893)))
(apply 'command (append '("pline") coords '("c")))
(setq currobj (ssadd (entlast) currobj))
(setq coords (list 
(list 2240.5625 -26.0463) 
(list 2314.585 -25.3963) 
(list 2314.585 -25.2193) 
(list 2240.5625 -25.9693)))
(apply 'command (append '("pline") coords '("c")))
(setq currobj (ssadd (entlast) currobj))
(setq coords (list 
(list 2239.4375 -25.9693) 
(list 2165.415 -25.2193) 
(list 2165.415 -25.3963) 
(list 2239.4375 -26.0463)))
(apply 'command (append '("pline") coords '("c")))
(setq currobj (ssadd (entlast) currobj))
(setq coords (list 
(list 2239.4375 -26.1893) 
(list 2165.415 -25.5393) 
(list 2165.415 -25.7163) 
(list 2239.4375 -26.2663)))
(apply 'command (append '("pline") coords '("c")))
(setq currobj (ssadd (entlast) currobj))
(setq coords (list 
(list 2239.4375 -26.4093) 
(list 2165.415 -25.8593) 
(list 2165.415 -26.0363) 
(list 2239.4375 -26.4863)))
(apply 'command (append '("pline") coords '("c")))
(setq currobj (ssadd (entlast) currobj))
(setq coords (list 
(list 2239.4375 -26.6293) 
(list 2165.415 -26.1793) 
(list 2165.415 -26.3563) 
(list 2239.4375 -26.7063)))
(apply 'command (append '("pline") coords '("c")))
(setq currobj (ssadd (entlast) currobj))
(setq coords (list 
(list 2239.4375 -26.8493) 
(list 2165.415 -26.4993) 
(list 2165.415 -26.6763) 
(list 2239.4375 -26.9263)))
(apply 'command (append '("pline") coords '("c")))
(setq currobj (ssadd (entlast) currobj))
(setq coords (list 
(list 2239.4375 -27.0693) 
(list 2165.415 -26.8193) 
(list 2165.415 -26.9963) 
(list 2239.4375 -27.1463)))
(apply 'command (append '("pline") coords '("c")))
(setq currobj (ssadd (entlast) currobj))
(setq coords (list 
(list 2239.4375 -27.2893) 
(list 2165.415 -27.1393) 
(list 2165.415 -27.3163) 
(list 2239.4375 -27.3663)))
(apply 'command (append '("pline") coords '("c")))
(setq currobj (ssadd (entlast) currobj))
(setq coords (list 
(list 2239.4375 -27.5093) 
(list 2165.415 -27.4593) 
(list 2165.415 -27.6363) 
(list 2239.4375 -27.5863)))
(apply 'command (append '("pline") coords '("c")))
(setq currobj (ssadd (entlast) currobj))
(setq coords (list 
(list 2239.4375 -27.7293) 
(list 2165.415 -27.7793) 
(list 2165.415 -27.9563) 
(list 2239.4375 -27.8063)))
(apply 'command (append '("pline") coords '("c")))
(setq currobj (ssadd (entlast) currobj))
(setq coords (list 
(list 2239.4375 -27.9493) 
(list 2165.415 -28.0993) 
(list 2165.415 -28.2763) 
(list 2239.4375 -28.0263)))
(apply 'command (append '("pline") coords '("c")))
(setq currobj (ssadd (entlast) currobj))
(setq coords (list 
(list 2239.4375 -28.1693) 
(list 2165.415 -28.4193) 
(list 2165.415 -28.5963) 
(list 2239.4375 -28.2463)))
(apply 'command (append '("pline") coords '("c")))
(setq currobj (ssadd (entlast) currobj))
(setq coords (list 
(list 2239.4375 -28.3893) 
(list 2165.415 -28.7393) 
(list 2165.415 -28.9163) 
(list 2239.4375 -28.4663)))
(apply 'command (append '("pline") coords '("c")))
(setq currobj (ssadd (entlast) currobj))
(setq coords (list 
(list 2239.4375 -28.6093) 
(list 2165.415 -29.0593) 
(list 2165.415 -29.2363) 
(list 2239.4375 -28.6863)))
(apply 'command (append '("pline") coords '("c")))
(setq currobj (ssadd (entlast) currobj))
(setq coords (list 
(list 2239.4375 -28.8293) 
(list 2165.415 -29.3793) 
(list 2165.415 -29.5563) 
(list 2239.4375 -28.9063)))
(apply 'command (append '("pline") coords '("c")))
(setq currobj (ssadd (entlast) currobj))
(setq coords (list 
(list 2239.4375 -29.0493) 
(list 2165.415 -29.6993) 
(list 2165.415 -29.8763) 
(list 2239.4375 -29.1263)))
(apply 'command (append '("pline") coords '("c")))
(setq currobj (ssadd (entlast) currobj))
(command "_layer" "set" "nitride" "")
(command "_layer" "set" "text" "")
(command "_circle" "2239.0625,-40.2693" "0.075")
(command "_circle" "2239.0625,-39.9693" "0.075")
(command "_circle" "2239.0625,-39.6693" "0.075")
(command "_circle" "2239.0625,-39.3693" "0.075")
(command "_circle" "2239.0625,-39.0693" "0.075")
(command "_circle" "2238.7625,-40.2693" "0.075")
(command "_circle" "2238.7625,-39.9693" "0.075")
(command "_circle" "2238.7625,-39.6693" "0.075")
(command "_circle" "2238.7625,-39.3693" "0.075")
(command "_circle" "2238.7625,-39.0693" "0.075")
(command "_circle" "2238.4625,-40.2693" "0.075")
(command "_circle" "2238.4625,-39.9693" "0.075")
(command "_circle" "2238.4625,-39.6693" "0.075")
(command "_circle" "2238.4625,-39.3693" "0.075")
(command "_circle" "2238.4625,-39.0693" "0.075")
(command "_circle" "2238.1625,-40.2693" "0.075")
(command "_circle" "2238.1625,-39.9693" "0.075")
(command "_circle" "2238.1625,-39.6693" "0.075")
(command "_circle" "2238.1625,-39.3693" "0.075")
(command "_circle" "2238.1625,-39.0693" "0.075")
(command "_circle" "2237.8625,-40.2693" "0.075")
(command "_circle" "2237.8625,-39.9693" "0.075")
(command "_circle" "2237.8625,-39.6693" "0.075")
(command "_circle" "2237.8625,-39.3693" "0.075")
(command "_circle" "2237.8625,-39.0693" "0.075")
(command "_layer" "set" "nitride" "")
(setq coords (list 
(list 2240.2625 -14.8263) 
(list 2240.2625 100.8184) 
(list 2239.7375 100.8184) 
(list 2239.7375 -14.8263)))
(apply 'command (append '("pline") coords '("c")))
(setq currobj (ssadd (entlast) currobj))
(command "_layer" "set" "prebias" "")
(command "_rectangle" "2239.7375,-14.8263" "2240.2625,100.8184")
(setq currobj (ssadd (entlast) currobj))
(command "_layer" "set" "nitride" "")
(setq coords (list 
(list 2240.2625 100.8184) 
(list 2240.5625 110.8184) 
(list 2240.5625 110.8184) 
(list 2240.5625 111.8184) 
(list 2314.585 111.0684) 
(list 2314.585 116.0114) 
(list 2240.5625 115.2614) 
(list 2240.5625 116.2614) 
(list 2240.5625 116.2614) 
(list 2240.2625 126.2614) 
(list 2239.7375 126.2614) 
(list 2239.4375 116.2614) 
(list 2239.4375 116.2614) 
(list 2239.4375 115.2614) 
(list 2165.415 116.0114) 
(list 2165.415 111.0684) 
(list 2239.4375 111.8184) 
(list 2239.4375 110.8184) 
(list 2239.4375 110.8184) 
(list 2239.7375 100.8184)))
(apply 'command (append '("pline") coords '("c")))
(setq currobj (ssadd (entlast) currobj))
(command "_layer" "set" "prebias" "")
(setq coords (list 
(list 2239.4375 100.8184) 
(list 2239.4375 111.8184) 
(list 2165.415 111.0684) 
(list 2165.415 116.0114) 
(list 2239.4375 115.2614) 
(list 2239.4375 126.2614) 
(list 2240.5625 126.2614) 
(list 2240.5625 115.2614) 
(list 2314.585 116.0114) 
(list 2314.585 111.0684) 
(list 2240.5625 111.8184) 
(list 2240.5625 100.8184)))
(apply 'command (append '("pline") coords '("c")))
(setq currobj (ssadd (entlast) currobj))
(command "_layer" "set" "nitride" "")
(command "_layer" "set" "fda1" "")
(setq coords (list 
(list 2240.5625 111.9614) 
(list 2314.585 111.2114) 
(list 2314.585 111.3884) 
(list 2240.5625 112.0384)))
(apply 'command (append '("pline") coords '("c")))
(setq currobj (ssadd (entlast) currobj))
(setq coords (list 
(list 2240.5625 112.1814) 
(list 2314.585 111.5314) 
(list 2314.585 111.7084) 
(list 2240.5625 112.2584)))
(apply 'command (append '("pline") coords '("c")))
(setq currobj (ssadd (entlast) currobj))
(setq coords (list 
(list 2240.5625 112.4014) 
(list 2314.585 111.8514) 
(list 2314.585 112.0284) 
(list 2240.5625 112.4784)))
(apply 'command (append '("pline") coords '("c")))
(setq currobj (ssadd (entlast) currobj))
(setq coords (list 
(list 2240.5625 112.6214) 
(list 2314.585 112.1714) 
(list 2314.585 112.3484) 
(list 2240.5625 112.6984)))
(apply 'command (append '("pline") coords '("c")))
(setq currobj (ssadd (entlast) currobj))
(setq coords (list 
(list 2240.5625 112.8414) 
(list 2314.585 112.4914) 
(list 2314.585 112.6684) 
(list 2240.5625 112.9184)))
(apply 'command (append '("pline") coords '("c")))
(setq currobj (ssadd (entlast) currobj))
(setq coords (list 
(list 2240.5625 113.0614) 
(list 2314.585 112.8114) 
(list 2314.585 112.9884) 
(list 2240.5625 113.1384)))
(apply 'command (append '("pline") coords '("c")))
(setq currobj (ssadd (entlast) currobj))
(setq coords (list 
(list 2240.5625 113.2814) 
(list 2314.585 113.1314) 
(list 2314.585 113.3084) 
(list 2240.5625 113.3584)))
(apply 'command (append '("pline") coords '("c")))
(setq currobj (ssadd (entlast) currobj))
(setq coords (list 
(list 2240.5625 113.5014) 
(list 2314.585 113.4514) 
(list 2314.585 113.6284) 
(list 2240.5625 113.5784)))
(apply 'command (append '("pline") coords '("c")))
(setq currobj (ssadd (entlast) currobj))
(setq coords (list 
(list 2240.5625 113.7214) 
(list 2314.585 113.7714) 
(list 2314.585 113.9484) 
(list 2240.5625 113.7984)))
(apply 'command (append '("pline") coords '("c")))
(setq currobj (ssadd (entlast) currobj))
(setq coords (list 
(list 2240.5625 113.9414) 
(list 2314.585 114.0914) 
(list 2314.585 114.2684) 
(list 2240.5625 114.0184)))
(apply 'command (append '("pline") coords '("c")))
(setq currobj (ssadd (entlast) currobj))
(setq coords (list 
(list 2240.5625 114.1614) 
(list 2314.585 114.4114) 
(list 2314.585 114.5884) 
(list 2240.5625 114.2384)))
(apply 'command (append '("pline") coords '("c")))
(setq currobj (ssadd (entlast) currobj))
(setq coords (list 
(list 2240.5625 114.3814) 
(list 2314.585 114.7314) 
(list 2314.585 114.9084) 
(list 2240.5625 114.4584)))
(apply 'command (append '("pline") coords '("c")))
(setq currobj (ssadd (entlast) currobj))
(setq coords (list 
(list 2240.5625 114.6014) 
(list 2314.585 115.0514) 
(list 2314.585 115.2284) 
(list 2240.5625 114.6784)))
(apply 'command (append '("pline") coords '("c")))
(setq currobj (ssadd (entlast) currobj))
(setq coords (list 
(list 2240.5625 114.8214) 
(list 2314.585 115.3714) 
(list 2314.585 115.5484) 
(list 2240.5625 114.8984)))
(apply 'command (append '("pline") coords '("c")))
(setq currobj (ssadd (entlast) currobj))
(setq coords (list 
(list 2240.5625 115.0414) 
(list 2314.585 115.6914) 
(list 2314.585 115.8684) 
(list 2240.5625 115.1184)))
(apply 'command (append '("pline") coords '("c")))
(setq currobj (ssadd (entlast) currobj))
(setq coords (list 
(list 2239.4375 115.1184) 
(list 2165.415 115.8684) 
(list 2165.415 115.6914) 
(list 2239.4375 115.0414)))
(apply 'command (append '("pline") coords '("c")))
(setq currobj (ssadd (entlast) currobj))
(setq coords (list 
(list 2239.4375 114.8984) 
(list 2165.415 115.5484) 
(list 2165.415 115.3714) 
(list 2239.4375 114.8214)))
(apply 'command (append '("pline") coords '("c")))
(setq currobj (ssadd (entlast) currobj))
(setq coords (list 
(list 2239.4375 114.6784) 
(list 2165.415 115.2284) 
(list 2165.415 115.0514) 
(list 2239.4375 114.6014)))
(apply 'command (append '("pline") coords '("c")))
(setq currobj (ssadd (entlast) currobj))
(setq coords (list 
(list 2239.4375 114.4584) 
(list 2165.415 114.9084) 
(list 2165.415 114.7314) 
(list 2239.4375 114.3814)))
(apply 'command (append '("pline") coords '("c")))
(setq currobj (ssadd (entlast) currobj))
(setq coords (list 
(list 2239.4375 114.2384) 
(list 2165.415 114.5884) 
(list 2165.415 114.4114) 
(list 2239.4375 114.1614)))
(apply 'command (append '("pline") coords '("c")))
(setq currobj (ssadd (entlast) currobj))
(setq coords (list 
(list 2239.4375 114.0184) 
(list 2165.415 114.2684) 
(list 2165.415 114.0914) 
(list 2239.4375 113.9414)))
(apply 'command (append '("pline") coords '("c")))
(setq currobj (ssadd (entlast) currobj))
(setq coords (list 
(list 2239.4375 113.7984) 
(list 2165.415 113.9484) 
(list 2165.415 113.7714) 
(list 2239.4375 113.7214)))
(apply 'command (append '("pline") coords '("c")))
(setq currobj (ssadd (entlast) currobj))
(setq coords (list 
(list 2239.4375 113.5784) 
(list 2165.415 113.6284) 
(list 2165.415 113.4514) 
(list 2239.4375 113.5014)))
(apply 'command (append '("pline") coords '("c")))
(setq currobj (ssadd (entlast) currobj))
(setq coords (list 
(list 2239.4375 113.3584) 
(list 2165.415 113.3084) 
(list 2165.415 113.1314) 
(list 2239.4375 113.2814)))
(apply 'command (append '("pline") coords '("c")))
(setq currobj (ssadd (entlast) currobj))
(setq coords (list 
(list 2239.4375 113.1384) 
(list 2165.415 112.9884) 
(list 2165.415 112.8114) 
(list 2239.4375 113.0614)))
(apply 'command (append '("pline") coords '("c")))
(setq currobj (ssadd (entlast) currobj))
(setq coords (list 
(list 2239.4375 112.9184) 
(list 2165.415 112.6684) 
(list 2165.415 112.4914) 
(list 2239.4375 112.8414)))
(apply 'command (append '("pline") coords '("c")))
(setq currobj (ssadd (entlast) currobj))
(setq coords (list 
(list 2239.4375 112.6984) 
(list 2165.415 112.3484) 
(list 2165.415 112.1714) 
(list 2239.4375 112.6214)))
(apply 'command (append '("pline") coords '("c")))
(setq currobj (ssadd (entlast) currobj))
(setq coords (list 
(list 2239.4375 112.4784) 
(list 2165.415 112.0284) 
(list 2165.415 111.8514) 
(list 2239.4375 112.4014)))
(apply 'command (append '("pline") coords '("c")))
(setq currobj (ssadd (entlast) currobj))
(setq coords (list 
(list 2239.4375 112.2584) 
(list 2165.415 111.7084) 
(list 2165.415 111.5314) 
(list 2239.4375 112.1814)))
(apply 'command (append '("pline") coords '("c")))
(setq currobj (ssadd (entlast) currobj))
(setq coords (list 
(list 2239.4375 112.0384) 
(list 2165.415 111.3884) 
(list 2165.415 111.2114) 
(list 2239.4375 111.9614)))
(apply 'command (append '("pline") coords '("c")))
(setq currobj (ssadd (entlast) currobj))
(command "_layer" "set" "nitride" "")
(command "_layer" "set" "text" "")
(command "_circle" "2239.0625,100.8184" "0.075")
(command "_circle" "2239.0625,101.1184" "0.075")
(command "_circle" "2239.0625,101.4184" "0.075")
(command "_circle" "2239.0625,101.7184" "0.075")
(command "_circle" "2239.0625,102.0184" "0.075")
(command "_circle" "2238.7625,100.8184" "0.075")
(command "_circle" "2238.7625,101.1184" "0.075")
(command "_circle" "2238.7625,101.4184" "0.075")
(command "_circle" "2238.7625,101.7184" "0.075")
(command "_circle" "2238.7625,102.0184" "0.075")
(command "_circle" "2238.4625,100.8184" "0.075")
(command "_circle" "2238.4625,101.1184" "0.075")
(command "_circle" "2238.4625,101.4184" "0.075")
(command "_circle" "2238.4625,101.7184" "0.075")
(command "_circle" "2238.4625,102.0184" "0.075")
(command "_circle" "2238.1625,100.8184" "0.075")
(command "_circle" "2238.1625,101.1184" "0.075")
(command "_circle" "2238.1625,101.4184" "0.075")
(command "_circle" "2238.1625,101.7184" "0.075")
(command "_circle" "2238.1625,102.0184" "0.075")
(command "_circle" "2237.8625,100.8184" "0.075")
(command "_circle" "2237.8625,101.1184" "0.075")
(command "_circle" "2237.8625,101.4184" "0.075")
(command "_circle" "2237.8625,101.7184" "0.075")
(command "_circle" "2237.8625,102.0184" "0.075")
(command "_layer" "set" "nitride" "")
(setq coords (list 
(list 2240.2625 126.2614) 
(list 2240.2625 241.9061) 
(list 2239.7375 241.9061) 
(list 2239.7375 126.2614)))
(apply 'command (append '("pline") coords '("c")))
(setq currobj (ssadd (entlast) currobj))
(command "_layer" "set" "prebias" "")
(command "_rectangle" "2239.7375,126.2614" "2240.2625,241.9061")
(setq currobj (ssadd (entlast) currobj))
(command "_layer" "set" "nitride" "")
(setq coords (list 
(list 2240.2625 241.9061) 
(list 2240.5625 251.9061) 
(list 2240.5625 251.9061) 
(list 2240.5625 252.9061) 
(list 2314.585 252.1561) 
(list 2314.585 257.0991) 
(list 2240.5625 256.3491) 
(list 2240.5625 257.3491) 
(list 2240.5625 257.3491) 
(list 2240.2625 267.3491) 
(list 2239.7375 267.3491) 
(list 2239.4375 257.3491) 
(list 2239.4375 257.3491) 
(list 2239.4375 256.3491) 
(list 2165.415 257.0991) 
(list 2165.415 252.1561) 
(list 2239.4375 252.9061) 
(list 2239.4375 251.9061) 
(list 2239.4375 251.9061) 
(list 2239.7375 241.9061)))
(apply 'command (append '("pline") coords '("c")))
(setq currobj (ssadd (entlast) currobj))
(command "_layer" "set" "prebias" "")
(setq coords (list 
(list 2239.4375 241.9061) 
(list 2239.4375 252.9061) 
(list 2165.415 252.1561) 
(list 2165.415 257.0991) 
(list 2239.4375 256.3491) 
(list 2239.4375 267.3491) 
(list 2240.5625 267.3491) 
(list 2240.5625 256.3491) 
(list 2314.585 257.0991) 
(list 2314.585 252.1561) 
(list 2240.5625 252.9061) 
(list 2240.5625 241.9061)))
(apply 'command (append '("pline") coords '("c")))
(setq currobj (ssadd (entlast) currobj))
(command "_layer" "set" "nitride" "")
(command "_layer" "set" "fda1" "")
(setq coords (list 
(list 2240.5625 253.0491) 
(list 2314.585 252.2991) 
(list 2314.585 252.4761) 
(list 2240.5625 253.1261)))
(apply 'command (append '("pline") coords '("c")))
(setq currobj (ssadd (entlast) currobj))
(setq coords (list 
(list 2240.5625 253.2691) 
(list 2314.585 252.6191) 
(list 2314.585 252.7961) 
(list 2240.5625 253.3461)))
(apply 'command (append '("pline") coords '("c")))
(setq currobj (ssadd (entlast) currobj))
(setq coords (list 
(list 2240.5625 253.4891) 
(list 2314.585 252.9391) 
(list 2314.585 253.1161) 
(list 2240.5625 253.5661)))
(apply 'command (append '("pline") coords '("c")))
(setq currobj (ssadd (entlast) currobj))
(setq coords (list 
(list 2240.5625 253.7091) 
(list 2314.585 253.2591) 
(list 2314.585 253.4361) 
(list 2240.5625 253.7861)))
(apply 'command (append '("pline") coords '("c")))
(setq currobj (ssadd (entlast) currobj))
(setq coords (list 
(list 2240.5625 253.9291) 
(list 2314.585 253.5791) 
(list 2314.585 253.7561) 
(list 2240.5625 254.0061)))
(apply 'command (append '("pline") coords '("c")))
(setq currobj (ssadd (entlast) currobj))
(setq coords (list 
(list 2240.5625 254.1491) 
(list 2314.585 253.8991) 
(list 2314.585 254.0761) 
(list 2240.5625 254.2261)))
(apply 'command (append '("pline") coords '("c")))
(setq currobj (ssadd (entlast) currobj))
(setq coords (list 
(list 2240.5625 254.3691) 
(list 2314.585 254.2191) 
(list 2314.585 254.3961) 
(list 2240.5625 254.4461)))
(apply 'command (append '("pline") coords '("c")))
(setq currobj (ssadd (entlast) currobj))
(setq coords (list 
(list 2240.5625 254.5891) 
(list 2314.585 254.5391) 
(list 2314.585 254.7161) 
(list 2240.5625 254.6661)))
(apply 'command (append '("pline") coords '("c")))
(setq currobj (ssadd (entlast) currobj))
(setq coords (list 
(list 2240.5625 254.8091) 
(list 2314.585 254.8591) 
(list 2314.585 255.0361) 
(list 2240.5625 254.8861)))
(apply 'command (append '("pline") coords '("c")))
(setq currobj (ssadd (entlast) currobj))
(setq coords (list 
(list 2240.5625 255.0291) 
(list 2314.585 255.1791) 
(list 2314.585 255.3561) 
(list 2240.5625 255.1061)))
(apply 'command (append '("pline") coords '("c")))
(setq currobj (ssadd (entlast) currobj))
(setq coords (list 
(list 2240.5625 255.2491) 
(list 2314.585 255.4991) 
(list 2314.585 255.6761) 
(list 2240.5625 255.3261)))
(apply 'command (append '("pline") coords '("c")))
(setq currobj (ssadd (entlast) currobj))
(setq coords (list 
(list 2240.5625 255.4691) 
(list 2314.585 255.8191) 
(list 2314.585 255.9961) 
(list 2240.5625 255.5461)))
(apply 'command (append '("pline") coords '("c")))
(setq currobj (ssadd (entlast) currobj))
(setq coords (list 
(list 2240.5625 255.6891) 
(list 2314.585 256.1391) 
(list 2314.585 256.3161) 
(list 2240.5625 255.7661)))
(apply 'command (append '("pline") coords '("c")))
(setq currobj (ssadd (entlast) currobj))
(setq coords (list 
(list 2240.5625 255.9091) 
(list 2314.585 256.4591) 
(list 2314.585 256.6361) 
(list 2240.5625 255.9861)))
(apply 'command (append '("pline") coords '("c")))
(setq currobj (ssadd (entlast) currobj))
(setq coords (list 
(list 2240.5625 256.1291) 
(list 2314.585 256.7791) 
(list 2314.585 256.9561) 
(list 2240.5625 256.2061)))
(apply 'command (append '("pline") coords '("c")))
(setq currobj (ssadd (entlast) currobj))
(setq coords (list 
(list 2239.4375 256.2061) 
(list 2165.415 256.9561) 
(list 2165.415 256.7791) 
(list 2239.4375 256.1291)))
(apply 'command (append '("pline") coords '("c")))
(setq currobj (ssadd (entlast) currobj))
(setq coords (list 
(list 2239.4375 255.9861) 
(list 2165.415 256.6361) 
(list 2165.415 256.4591) 
(list 2239.4375 255.9091)))
(apply 'command (append '("pline") coords '("c")))
(setq currobj (ssadd (entlast) currobj))
(setq coords (list 
(list 2239.4375 255.7661) 
(list 2165.415 256.3161) 
(list 2165.415 256.1391) 
(list 2239.4375 255.6891)))
(apply 'command (append '("pline") coords '("c")))
(setq currobj (ssadd (entlast) currobj))
(setq coords (list 
(list 2239.4375 255.5461) 
(list 2165.415 255.9961) 
(list 2165.415 255.8191) 
(list 2239.4375 255.4691)))
(apply 'command (append '("pline") coords '("c")))
(setq currobj (ssadd (entlast) currobj))
(setq coords (list 
(list 2239.4375 255.3261) 
(list 2165.415 255.6761) 
(list 2165.415 255.4991) 
(list 2239.4375 255.2491)))
(apply 'command (append '("pline") coords '("c")))
(setq currobj (ssadd (entlast) currobj))
(setq coords (list 
(list 2239.4375 255.1061) 
(list 2165.415 255.3561) 
(list 2165.415 255.1791) 
(list 2239.4375 255.0291)))
(apply 'command (append '("pline") coords '("c")))
(setq currobj (ssadd (entlast) currobj))
(setq coords (list 
(list 2239.4375 254.8861) 
(list 2165.415 255.0361) 
(list 2165.415 254.8591) 
(list 2239.4375 254.8091)))
(apply 'command (append '("pline") coords '("c")))
(setq currobj (ssadd (entlast) currobj))
(setq coords (list 
(list 2239.4375 254.6661) 
(list 2165.415 254.7161) 
(list 2165.415 254.5391) 
(list 2239.4375 254.5891)))
(apply 'command (append '("pline") coords '("c")))
(setq currobj (ssadd (entlast) currobj))
(setq coords (list 
(list 2239.4375 254.4461) 
(list 2165.415 254.3961) 
(list 2165.415 254.2191) 
(list 2239.4375 254.3691)))
(apply 'command (append '("pline") coords '("c")))
(setq currobj (ssadd (entlast) currobj))
(setq coords (list 
(list 2239.4375 254.2261) 
(list 2165.415 254.0761) 
(list 2165.415 253.8991) 
(list 2239.4375 254.1491)))
(apply 'command (append '("pline") coords '("c")))
(setq currobj (ssadd (entlast) currobj))
(setq coords (list 
(list 2239.4375 254.0061) 
(list 2165.415 253.7561) 
(list 2165.415 253.5791) 
(list 2239.4375 253.9291)))
(apply 'command (append '("pline") coords '("c")))
(setq currobj (ssadd (entlast) currobj))
(setq coords (list 
(list 2239.4375 253.7861) 
(list 2165.415 253.4361) 
(list 2165.415 253.2591) 
(list 2239.4375 253.7091)))
(apply 'command (append '("pline") coords '("c")))
(setq currobj (ssadd (entlast) currobj))
(setq coords (list 
(list 2239.4375 253.5661) 
(list 2165.415 253.1161) 
(list 2165.415 252.9391) 
(list 2239.4375 253.4891)))
(apply 'command (append '("pline") coords '("c")))
(setq currobj (ssadd (entlast) currobj))
(setq coords (list 
(list 2239.4375 253.3461) 
(list 2165.415 252.7961) 
(list 2165.415 252.6191) 
(list 2239.4375 253.2691)))
(apply 'command (append '("pline") coords '("c")))
(setq currobj (ssadd (entlast) currobj))
(setq coords (list 
(list 2239.4375 253.1261) 
(list 2165.415 252.4761) 
(list 2165.415 252.2991) 
(list 2239.4375 253.0491)))
(apply 'command (append '("pline") coords '("c")))
(setq currobj (ssadd (entlast) currobj))
(command "_layer" "set" "nitride" "")
(command "_layer" "set" "text" "")
(command "_circle" "2239.0625,241.9061" "0.075")
(command "_circle" "2239.0625,242.2061" "0.075")
(command "_circle" "2239.0625,242.5061" "0.075")
(command "_circle" "2239.0625,242.8061" "0.075")
(command "_circle" "2239.0625,243.1061" "0.075")
(command "_circle" "2238.7625,241.9061" "0.075")
(command "_circle" "2238.7625,242.2061" "0.075")
(command "_circle" "2238.7625,242.5061" "0.075")
(command "_circle" "2238.7625,242.8061" "0.075")
(command "_circle" "2238.7625,243.1061" "0.075")
(command "_circle" "2238.4625,241.9061" "0.075")
(command "_circle" "2238.4625,242.2061" "0.075")
(command "_circle" "2238.4625,242.5061" "0.075")
(command "_circle" "2238.4625,242.8061" "0.075")
(command "_circle" "2238.4625,243.1061" "0.075")
(command "_circle" "2238.1625,241.9061" "0.075")
(command "_circle" "2238.1625,242.2061" "0.075")
(command "_circle" "2238.1625,242.5061" "0.075")
(command "_circle" "2238.1625,242.8061" "0.075")
(command "_circle" "2238.1625,243.1061" "0.075")
(command "_circle" "2237.8625,241.9061" "0.075")
(command "_circle" "2237.8625,242.2061" "0.075")
(command "_circle" "2237.8625,242.5061" "0.075")
(command "_circle" "2237.8625,242.8061" "0.075")
(command "_circle" "2237.8625,243.1061" "0.075")
(command "_layer" "set" "nitride" "")
(setq coords (list 
(list 2240.2625 267.3491) 
(list 2240.2625 382.9939) 
(list 2239.7375 382.9939) 
(list 2239.7375 267.3491)))
(apply 'command (append '("pline") coords '("c")))
(setq currobj (ssadd (entlast) currobj))
(command "_layer" "set" "prebias" "")
(command "_rectangle" "2239.7375,267.3491" "2240.2625,382.9939")
(setq currobj (ssadd (entlast) currobj))
(command "_layer" "set" "nitride" "")
(setq coords (list 
(list 2240.2625 382.9939) 
(list 2240.5625 392.9939) 
(list 2240.5625 392.9939) 
(list 2240.5625 393.9939) 
(list 2314.585 393.2439) 
(list 2314.585 398.1869) 
(list 2240.5625 397.4369) 
(list 2240.5625 398.4369) 
(list 2240.5625 398.4369) 
(list 2240.2625 408.4369) 
(list 2239.7375 408.4369) 
(list 2239.4375 398.4369) 
(list 2239.4375 398.4369) 
(list 2239.4375 397.4369) 
(list 2165.415 398.1869) 
(list 2165.415 393.2439) 
(list 2239.4375 393.9939) 
(list 2239.4375 392.9939) 
(list 2239.4375 392.9939) 
(list 2239.7375 382.9939)))
(apply 'command (append '("pline") coords '("c")))
(setq currobj (ssadd (entlast) currobj))
(command "_layer" "set" "prebias" "")
(setq coords (list 
(list 2239.4375 382.9939) 
(list 2239.4375 393.9939) 
(list 2165.415 393.2439) 
(list 2165.415 398.1869) 
(list 2239.4375 397.4369) 
(list 2239.4375 408.4369) 
(list 2240.5625 408.4369) 
(list 2240.5625 397.4369) 
(list 2314.585 398.1869) 
(list 2314.585 393.2439) 
(list 2240.5625 393.9939) 
(list 2240.5625 382.9939)))
(apply 'command (append '("pline") coords '("c")))
(setq currobj (ssadd (entlast) currobj))
(command "_layer" "set" "nitride" "")
(command "_layer" "set" "fda1" "")
(setq coords (list 
(list 2240.5625 394.1369) 
(list 2314.585 393.3869) 
(list 2314.585 393.5639) 
(list 2240.5625 394.2139)))
(apply 'command (append '("pline") coords '("c")))
(setq currobj (ssadd (entlast) currobj))
(setq coords (list 
(list 2240.5625 394.3569) 
(list 2314.585 393.7069) 
(list 2314.585 393.8839) 
(list 2240.5625 394.4339)))
(apply 'command (append '("pline") coords '("c")))
(setq currobj (ssadd (entlast) currobj))
(setq coords (list 
(list 2240.5625 394.5769) 
(list 2314.585 394.0269) 
(list 2314.585 394.2039) 
(list 2240.5625 394.6539)))
(apply 'command (append '("pline") coords '("c")))
(setq currobj (ssadd (entlast) currobj))
(setq coords (list 
(list 2240.5625 394.7969) 
(list 2314.585 394.3469) 
(list 2314.585 394.5239) 
(list 2240.5625 394.8739)))
(apply 'command (append '("pline") coords '("c")))
(setq currobj (ssadd (entlast) currobj))
(setq coords (list 
(list 2240.5625 395.0169) 
(list 2314.585 394.6669) 
(list 2314.585 394.8439) 
(list 2240.5625 395.0939)))
(apply 'command (append '("pline") coords '("c")))
(setq currobj (ssadd (entlast) currobj))
(setq coords (list 
(list 2240.5625 395.2369) 
(list 2314.585 394.9869) 
(list 2314.585 395.1639) 
(list 2240.5625 395.3139)))
(apply 'command (append '("pline") coords '("c")))
(setq currobj (ssadd (entlast) currobj))
(setq coords (list 
(list 2240.5625 395.4569) 
(list 2314.585 395.3069) 
(list 2314.585 395.4839) 
(list 2240.5625 395.5339)))
(apply 'command (append '("pline") coords '("c")))
(setq currobj (ssadd (entlast) currobj))
(setq coords (list 
(list 2240.5625 395.6769) 
(list 2314.585 395.6269) 
(list 2314.585 395.8039) 
(list 2240.5625 395.7539)))
(apply 'command (append '("pline") coords '("c")))
(setq currobj (ssadd (entlast) currobj))
(setq coords (list 
(list 2240.5625 395.8969) 
(list 2314.585 395.9469) 
(list 2314.585 396.1239) 
(list 2240.5625 395.9739)))
(apply 'command (append '("pline") coords '("c")))
(setq currobj (ssadd (entlast) currobj))
(setq coords (list 
(list 2240.5625 396.1169) 
(list 2314.585 396.2669) 
(list 2314.585 396.4439) 
(list 2240.5625 396.1939)))
(apply 'command (append '("pline") coords '("c")))
(setq currobj (ssadd (entlast) currobj))
(setq coords (list 
(list 2240.5625 396.3369) 
(list 2314.585 396.5869) 
(list 2314.585 396.7639) 
(list 2240.5625 396.4139)))
(apply 'command (append '("pline") coords '("c")))
(setq currobj (ssadd (entlast) currobj))
(setq coords (list 
(list 2240.5625 396.5569) 
(list 2314.585 396.9069) 
(list 2314.585 397.0839) 
(list 2240.5625 396.6339)))
(apply 'command (append '("pline") coords '("c")))
(setq currobj (ssadd (entlast) currobj))
(setq coords (list 
(list 2240.5625 396.7769) 
(list 2314.585 397.2269) 
(list 2314.585 397.4039) 
(list 2240.5625 396.8539)))
(apply 'command (append '("pline") coords '("c")))
(setq currobj (ssadd (entlast) currobj))
(setq coords (list 
(list 2240.5625 396.9969) 
(list 2314.585 397.5469) 
(list 2314.585 397.7239) 
(list 2240.5625 397.0739)))
(apply 'command (append '("pline") coords '("c")))
(setq currobj (ssadd (entlast) currobj))
(setq coords (list 
(list 2240.5625 397.2169) 
(list 2314.585 397.8669) 
(list 2314.585 398.0439) 
(list 2240.5625 397.2939)))
(apply 'command (append '("pline") coords '("c")))
(setq currobj (ssadd (entlast) currobj))
(setq coords (list 
(list 2239.4375 397.2939) 
(list 2165.415 398.0439) 
(list 2165.415 397.8669) 
(list 2239.4375 397.2169)))
(apply 'command (append '("pline") coords '("c")))
(setq currobj (ssadd (entlast) currobj))
(setq coords (list 
(list 2239.4375 397.0739) 
(list 2165.415 397.7239) 
(list 2165.415 397.5469) 
(list 2239.4375 396.9969)))
(apply 'command (append '("pline") coords '("c")))
(setq currobj (ssadd (entlast) currobj))
(setq coords (list 
(list 2239.4375 396.8539) 
(list 2165.415 397.4039) 
(list 2165.415 397.2269) 
(list 2239.4375 396.7769)))
(apply 'command (append '("pline") coords '("c")))
(setq currobj (ssadd (entlast) currobj))
(setq coords (list 
(list 2239.4375 396.6339) 
(list 2165.415 397.0839) 
(list 2165.415 396.9069) 
(list 2239.4375 396.5569)))
(apply 'command (append '("pline") coords '("c")))
(setq currobj (ssadd (entlast) currobj))
(setq coords (list 
(list 2239.4375 396.4139) 
(list 2165.415 396.7639) 
(list 2165.415 396.5869) 
(list 2239.4375 396.3369)))
(apply 'command (append '("pline") coords '("c")))
(setq currobj (ssadd (entlast) currobj))
(setq coords (list 
(list 2239.4375 396.1939) 
(list 2165.415 396.4439) 
(list 2165.415 396.2669) 
(list 2239.4375 396.1169)))
(apply 'command (append '("pline") coords '("c")))
(setq currobj (ssadd (entlast) currobj))
(setq coords (list 
(list 2239.4375 395.9739) 
(list 2165.415 396.1239) 
(list 2165.415 395.9469) 
(list 2239.4375 395.8969)))
(apply 'command (append '("pline") coords '("c")))
(setq currobj (ssadd (entlast) currobj))
(setq coords (list 
(list 2239.4375 395.7539) 
(list 2165.415 395.8039) 
(list 2165.415 395.6269) 
(list 2239.4375 395.6769)))
(apply 'command (append '("pline") coords '("c")))
(setq currobj (ssadd (entlast) currobj))
(setq coords (list 
(list 2239.4375 395.5339) 
(list 2165.415 395.4839) 
(list 2165.415 395.3069) 
(list 2239.4375 395.4569)))
(apply 'command (append '("pline") coords '("c")))
(setq currobj (ssadd (entlast) currobj))
(setq coords (list 
(list 2239.4375 395.3139) 
(list 2165.415 395.1639) 
(list 2165.415 394.9869) 
(list 2239.4375 395.2369)))
(apply 'command (append '("pline") coords '("c")))
(setq currobj (ssadd (entlast) currobj))
(setq coords (list 
(list 2239.4375 395.0939) 
(list 2165.415 394.8439) 
(list 2165.415 394.6669) 
(list 2239.4375 395.0169)))
(apply 'command (append '("pline") coords '("c")))
(setq currobj (ssadd (entlast) currobj))
(setq coords (list 
(list 2239.4375 394.8739) 
(list 2165.415 394.5239) 
(list 2165.415 394.3469) 
(list 2239.4375 394.7969)))
(apply 'command (append '("pline") coords '("c")))
(setq currobj (ssadd (entlast) currobj))
(setq coords (list 
(list 2239.4375 394.6539) 
(list 2165.415 394.2039) 
(list 2165.415 394.0269) 
(list 2239.4375 394.5769)))
(apply 'command (append '("pline") coords '("c")))
(setq currobj (ssadd (entlast) currobj))
(setq coords (list 
(list 2239.4375 394.4339) 
(list 2165.415 393.8839) 
(list 2165.415 393.7069) 
(list 2239.4375 394.3569)))
(apply 'command (append '("pline") coords '("c")))
(setq currobj (ssadd (entlast) currobj))
(setq coords (list 
(list 2239.4375 394.2139) 
(list 2165.415 393.5639) 
(list 2165.415 393.3869) 
(list 2239.4375 394.1369)))
(apply 'command (append '("pline") coords '("c")))
(setq currobj (ssadd (entlast) currobj))
(command "_layer" "set" "nitride" "")
(command "_layer" "set" "text" "")
(command "_circle" "2239.0625,382.9939" "0.075")
(command "_circle" "2239.0625,383.2939" "0.075")
(command "_circle" "2239.0625,383.5939" "0.075")
(command "_circle" "2239.0625,383.8939" "0.075")
(command "_circle" "2239.0625,384.1939" "0.075")
(command "_circle" "2238.7625,382.9939" "0.075")
(command "_circle" "2238.7625,383.2939" "0.075")
(command "_circle" "2238.7625,383.5939" "0.075")
(command "_circle" "2238.7625,383.8939" "0.075")
(command "_circle" "2238.7625,384.1939" "0.075")
(command "_circle" "2238.4625,382.9939" "0.075")
(command "_circle" "2238.4625,383.2939" "0.075")
(command "_circle" "2238.4625,383.5939" "0.075")
(command "_circle" "2238.4625,383.8939" "0.075")
(command "_circle" "2238.4625,384.1939" "0.075")
(command "_circle" "2238.1625,382.9939" "0.075")
(command "_circle" "2238.1625,383.2939" "0.075")
(command "_circle" "2238.1625,383.5939" "0.075")
(command "_circle" "2238.1625,383.8939" "0.075")
(command "_circle" "2238.1625,384.1939" "0.075")
(command "_circle" "2237.8625,382.9939" "0.075")
(command "_circle" "2237.8625,383.2939" "0.075")
(command "_circle" "2237.8625,383.5939" "0.075")
(command "_circle" "2237.8625,383.8939" "0.075")
(command "_circle" "2237.8625,384.1939" "0.075")
(command "_layer" "set" "nitride" "")
(setq coords (list 
(list 2240.2625 408.4369) 
(list 2240.2625 524.0816) 
(list 2239.7375 524.0816) 
(list 2239.7375 408.4369)))
(apply 'command (append '("pline") coords '("c")))
(setq currobj (ssadd (entlast) currobj))
(command "_layer" "set" "prebias" "")
(command "_rectangle" "2239.7375,408.4369" "2240.2625,524.0816")
(setq currobj (ssadd (entlast) currobj))
(command "_layer" "set" "nitride" "")
(setq coords (list 
(list 2240.2625 524.0816) 
(list 2240.5625 534.0816) 
(list 2240.5625 534.0816) 
(list 2240.5625 535.0816) 
(list 2314.585 534.3316) 
(list 2314.585 539.2746) 
(list 2240.5625 538.5246) 
(list 2240.5625 539.5246) 
(list 2240.5625 539.5246) 
(list 2240.2625 549.5246) 
(list 2239.7375 549.5246) 
(list 2239.4375 539.5246) 
(list 2239.4375 539.5246) 
(list 2239.4375 538.5246) 
(list 2165.415 539.2746) 
(list 2165.415 534.3316) 
(list 2239.4375 535.0816) 
(list 2239.4375 534.0816) 
(list 2239.4375 534.0816) 
(list 2239.7375 524.0816)))
(apply 'command (append '("pline") coords '("c")))
(setq currobj (ssadd (entlast) currobj))
(command "_layer" "set" "prebias" "")
(setq coords (list 
(list 2239.4375 524.0816) 
(list 2239.4375 535.0816) 
(list 2165.415 534.3316) 
(list 2165.415 539.2746) 
(list 2239.4375 538.5246) 
(list 2239.4375 549.5246) 
(list 2240.5625 549.5246) 
(list 2240.5625 538.5246) 
(list 2314.585 539.2746) 
(list 2314.585 534.3316) 
(list 2240.5625 535.0816) 
(list 2240.5625 524.0816)))
(apply 'command (append '("pline") coords '("c")))
(setq currobj (ssadd (entlast) currobj))
(command "_layer" "set" "nitride" "")
(command "_layer" "set" "fda1" "")
(setq coords (list 
(list 2240.5625 535.2246) 
(list 2314.585 534.4746) 
(list 2314.585 534.6516) 
(list 2240.5625 535.3016)))
(apply 'command (append '("pline") coords '("c")))
(setq currobj (ssadd (entlast) currobj))
(setq coords (list 
(list 2240.5625 535.4446) 
(list 2314.585 534.7946) 
(list 2314.585 534.9716) 
(list 2240.5625 535.5216)))
(apply 'command (append '("pline") coords '("c")))
(setq currobj (ssadd (entlast) currobj))
(setq coords (list 
(list 2240.5625 535.6646) 
(list 2314.585 535.1146) 
(list 2314.585 535.2916) 
(list 2240.5625 535.7416)))
(apply 'command (append '("pline") coords '("c")))
(setq currobj (ssadd (entlast) currobj))
(setq coords (list 
(list 2240.5625 535.8846) 
(list 2314.585 535.4346) 
(list 2314.585 535.6116) 
(list 2240.5625 535.9616)))
(apply 'command (append '("pline") coords '("c")))
(setq currobj (ssadd (entlast) currobj))
(setq coords (list 
(list 2240.5625 536.1046) 
(list 2314.585 535.7546) 
(list 2314.585 535.9316) 
(list 2240.5625 536.1816)))
(apply 'command (append '("pline") coords '("c")))
(setq currobj (ssadd (entlast) currobj))
(setq coords (list 
(list 2240.5625 536.3246) 
(list 2314.585 536.0746) 
(list 2314.585 536.2516) 
(list 2240.5625 536.4016)))
(apply 'command (append '("pline") coords '("c")))
(setq currobj (ssadd (entlast) currobj))
(setq coords (list 
(list 2240.5625 536.5446) 
(list 2314.585 536.3946) 
(list 2314.585 536.5716) 
(list 2240.5625 536.6216)))
(apply 'command (append '("pline") coords '("c")))
(setq currobj (ssadd (entlast) currobj))
(setq coords (list 
(list 2240.5625 536.7646) 
(list 2314.585 536.7146) 
(list 2314.585 536.8916) 
(list 2240.5625 536.8416)))
(apply 'command (append '("pline") coords '("c")))
(setq currobj (ssadd (entlast) currobj))
(setq coords (list 
(list 2240.5625 536.9846) 
(list 2314.585 537.0346) 
(list 2314.585 537.2116) 
(list 2240.5625 537.0616)))
(apply 'command (append '("pline") coords '("c")))
(setq currobj (ssadd (entlast) currobj))
(setq coords (list 
(list 2240.5625 537.2046) 
(list 2314.585 537.3546) 
(list 2314.585 537.5316) 
(list 2240.5625 537.2816)))
(apply 'command (append '("pline") coords '("c")))
(setq currobj (ssadd (entlast) currobj))
(setq coords (list 
(list 2240.5625 537.4246) 
(list 2314.585 537.6746) 
(list 2314.585 537.8516) 
(list 2240.5625 537.5016)))
(apply 'command (append '("pline") coords '("c")))
(setq currobj (ssadd (entlast) currobj))
(setq coords (list 
(list 2240.5625 537.6446) 
(list 2314.585 537.9946) 
(list 2314.585 538.1716) 
(list 2240.5625 537.7216)))
(apply 'command (append '("pline") coords '("c")))
(setq currobj (ssadd (entlast) currobj))
(setq coords (list 
(list 2240.5625 537.8646) 
(list 2314.585 538.3146) 
(list 2314.585 538.4916) 
(list 2240.5625 537.9416)))
(apply 'command (append '("pline") coords '("c")))
(setq currobj (ssadd (entlast) currobj))
(setq coords (list 
(list 2240.5625 538.0846) 
(list 2314.585 538.6346) 
(list 2314.585 538.8116) 
(list 2240.5625 538.1616)))
(apply 'command (append '("pline") coords '("c")))
(setq currobj (ssadd (entlast) currobj))
(setq coords (list 
(list 2240.5625 538.3046) 
(list 2314.585 538.9546) 
(list 2314.585 539.1316) 
(list 2240.5625 538.3816)))
(apply 'command (append '("pline") coords '("c")))
(setq currobj (ssadd (entlast) currobj))
(setq coords (list 
(list 2239.4375 538.3816) 
(list 2165.415 539.1316) 
(list 2165.415 538.9546) 
(list 2239.4375 538.3046)))
(apply 'command (append '("pline") coords '("c")))
(setq currobj (ssadd (entlast) currobj))
(setq coords (list 
(list 2239.4375 538.1616) 
(list 2165.415 538.8116) 
(list 2165.415 538.6346) 
(list 2239.4375 538.0846)))
(apply 'command (append '("pline") coords '("c")))
(setq currobj (ssadd (entlast) currobj))
(setq coords (list 
(list 2239.4375 537.9416) 
(list 2165.415 538.4916) 
(list 2165.415 538.3146) 
(list 2239.4375 537.8646)))
(apply 'command (append '("pline") coords '("c")))
(setq currobj (ssadd (entlast) currobj))
(setq coords (list 
(list 2239.4375 537.7216) 
(list 2165.415 538.1716) 
(list 2165.415 537.9946) 
(list 2239.4375 537.6446)))
(apply 'command (append '("pline") coords '("c")))
(setq currobj (ssadd (entlast) currobj))
(setq coords (list 
(list 2239.4375 537.5016) 
(list 2165.415 537.8516) 
(list 2165.415 537.6746) 
(list 2239.4375 537.4246)))
(apply 'command (append '("pline") coords '("c")))
(setq currobj (ssadd (entlast) currobj))
(setq coords (list 
(list 2239.4375 537.2816) 
(list 2165.415 537.5316) 
(list 2165.415 537.3546) 
(list 2239.4375 537.2046)))
(apply 'command (append '("pline") coords '("c")))
(setq currobj (ssadd (entlast) currobj))
(setq coords (list 
(list 2239.4375 537.0616) 
(list 2165.415 537.2116) 
(list 2165.415 537.0346) 
(list 2239.4375 536.9846)))
(apply 'command (append '("pline") coords '("c")))
(setq currobj (ssadd (entlast) currobj))
(setq coords (list 
(list 2239.4375 536.8416) 
(list 2165.415 536.8916) 
(list 2165.415 536.7146) 
(list 2239.4375 536.7646)))
(apply 'command (append '("pline") coords '("c")))
(setq currobj (ssadd (entlast) currobj))
(setq coords (list 
(list 2239.4375 536.6216) 
(list 2165.415 536.5716) 
(list 2165.415 536.3946) 
(list 2239.4375 536.5446)))
(apply 'command (append '("pline") coords '("c")))
(setq currobj (ssadd (entlast) currobj))
(setq coords (list 
(list 2239.4375 536.4016) 
(list 2165.415 536.2516) 
(list 2165.415 536.0746) 
(list 2239.4375 536.3246)))
(apply 'command (append '("pline") coords '("c")))
(setq currobj (ssadd (entlast) currobj))
(setq coords (list 
(list 2239.4375 536.1816) 
(list 2165.415 535.9316) 
(list 2165.415 535.7546) 
(list 2239.4375 536.1046)))
(apply 'command (append '("pline") coords '("c")))
(setq currobj (ssadd (entlast) currobj))
(setq coords (list 
(list 2239.4375 535.9616) 
(list 2165.415 535.6116) 
(list 2165.415 535.4346) 
(list 2239.4375 535.8846)))
(apply 'command (append '("pline") coords '("c")))
(setq currobj (ssadd (entlast) currobj))
(setq coords (list 
(list 2239.4375 535.7416) 
(list 2165.415 535.2916) 
(list 2165.415 535.1146) 
(list 2239.4375 535.6646)))
(apply 'command (append '("pline") coords '("c")))
(setq currobj (ssadd (entlast) currobj))
(setq coords (list 
(list 2239.4375 535.5216) 
(list 2165.415 534.9716) 
(list 2165.415 534.7946) 
(list 2239.4375 535.4446)))
(apply 'command (append '("pline") coords '("c")))
(setq currobj (ssadd (entlast) currobj))
(setq coords (list 
(list 2239.4375 535.3016) 
(list 2165.415 534.6516) 
(list 2165.415 534.4746) 
(list 2239.4375 535.2246)))
(apply 'command (append '("pline") coords '("c")))
(setq currobj (ssadd (entlast) currobj))
(command "_layer" "set" "nitride" "")
(command "_layer" "set" "text" "")
(command "_circle" "2239.0625,524.0816" "0.075")
(command "_circle" "2239.0625,524.3816" "0.075")
(command "_circle" "2239.0625,524.6816" "0.075")
(command "_circle" "2239.0625,524.9816" "0.075")
(command "_circle" "2239.0625,525.2816" "0.075")
(command "_circle" "2238.7625,524.0816" "0.075")
(command "_circle" "2238.7625,524.3816" "0.075")
(command "_circle" "2238.7625,524.6816" "0.075")
(command "_circle" "2238.7625,524.9816" "0.075")
(command "_circle" "2238.7625,525.2816" "0.075")
(command "_circle" "2238.4625,524.0816" "0.075")
(command "_circle" "2238.4625,524.3816" "0.075")
(command "_circle" "2238.4625,524.6816" "0.075")
(command "_circle" "2238.4625,524.9816" "0.075")
(command "_circle" "2238.4625,525.2816" "0.075")
(command "_circle" "2238.1625,524.0816" "0.075")
(command "_circle" "2238.1625,524.3816" "0.075")
(command "_circle" "2238.1625,524.6816" "0.075")
(command "_circle" "2238.1625,524.9816" "0.075")
(command "_circle" "2238.1625,525.2816" "0.075")
(command "_circle" "2237.8625,524.0816" "0.075")
(command "_circle" "2237.8625,524.3816" "0.075")
(command "_circle" "2237.8625,524.6816" "0.075")
(command "_circle" "2237.8625,524.9816" "0.075")
(command "_circle" "2237.8625,525.2816" "0.075")
(command "_layer" "set" "nitride" "")
(setq coords (list 
(list 2240.2625 549.5246) 
(list 2240.2625 665.1693) 
(list 2239.7375 665.1693) 
(list 2239.7375 549.5246)))
(apply 'command (append '("pline") coords '("c")))
(setq currobj (ssadd (entlast) currobj))
(command "_layer" "set" "prebias" "")
(command "_rectangle" "2239.7375,549.5246" "2240.2625,665.1693")
(setq currobj (ssadd (entlast) currobj))
(command "_layer" "set" "nitride" "")
(setq coords (list 
(list 2240.2625 665.1693) 
(list 2240.5625 675.1693) 
(list 2240.5625 675.1693) 
(list 2240.5625 676.1693) 
(list 2314.585 675.4193) 
(list 2314.585 680.3623) 
(list 2240.5625 679.6123) 
(list 2240.5625 680.6123) 
(list 2240.5625 680.6123) 
(list 2240.2625 690.6123) 
(list 2239.7375 690.6123) 
(list 2239.4375 680.6123) 
(list 2239.4375 680.6123) 
(list 2239.4375 679.6123) 
(list 2165.415 680.3623) 
(list 2165.415 675.4193) 
(list 2239.4375 676.1693) 
(list 2239.4375 675.1693) 
(list 2239.4375 675.1693) 
(list 2239.7375 665.1693)))
(apply 'command (append '("pline") coords '("c")))
(setq currobj (ssadd (entlast) currobj))
(command "_layer" "set" "prebias" "")
(setq coords (list 
(list 2239.4375 665.1693) 
(list 2239.4375 676.1693) 
(list 2165.415 675.4193) 
(list 2165.415 680.3623) 
(list 2239.4375 679.6123) 
(list 2239.4375 690.6123) 
(list 2240.5625 690.6123) 
(list 2240.5625 679.6123) 
(list 2314.585 680.3623) 
(list 2314.585 675.4193) 
(list 2240.5625 676.1693) 
(list 2240.5625 665.1693)))
(apply 'command (append '("pline") coords '("c")))
(setq currobj (ssadd (entlast) currobj))
(command "_layer" "set" "nitride" "")
(command "_layer" "set" "fda1" "")
(setq coords (list 
(list 2240.5625 676.3123) 
(list 2314.585 675.5623) 
(list 2314.585 675.7393) 
(list 2240.5625 676.3893)))
(apply 'command (append '("pline") coords '("c")))
(setq currobj (ssadd (entlast) currobj))
(setq coords (list 
(list 2240.5625 676.5323) 
(list 2314.585 675.8823) 
(list 2314.585 676.0593) 
(list 2240.5625 676.6093)))
(apply 'command (append '("pline") coords '("c")))
(setq currobj (ssadd (entlast) currobj))
(setq coords (list 
(list 2240.5625 676.7523) 
(list 2314.585 676.2023) 
(list 2314.585 676.3793) 
(list 2240.5625 676.8293)))
(apply 'command (append '("pline") coords '("c")))
(setq currobj (ssadd (entlast) currobj))
(setq coords (list 
(list 2240.5625 676.9723) 
(list 2314.585 676.5223) 
(list 2314.585 676.6993) 
(list 2240.5625 677.0493)))
(apply 'command (append '("pline") coords '("c")))
(setq currobj (ssadd (entlast) currobj))
(setq coords (list 
(list 2240.5625 677.1923) 
(list 2314.585 676.8423) 
(list 2314.585 677.0193) 
(list 2240.5625 677.2693)))
(apply 'command (append '("pline") coords '("c")))
(setq currobj (ssadd (entlast) currobj))
(setq coords (list 
(list 2240.5625 677.4123) 
(list 2314.585 677.1623) 
(list 2314.585 677.3393) 
(list 2240.5625 677.4893)))
(apply 'command (append '("pline") coords '("c")))
(setq currobj (ssadd (entlast) currobj))
(setq coords (list 
(list 2240.5625 677.6323) 
(list 2314.585 677.4823) 
(list 2314.585 677.6593) 
(list 2240.5625 677.7093)))
(apply 'command (append '("pline") coords '("c")))
(setq currobj (ssadd (entlast) currobj))
(setq coords (list 
(list 2240.5625 677.8523) 
(list 2314.585 677.8023) 
(list 2314.585 677.9793) 
(list 2240.5625 677.9293)))
(apply 'command (append '("pline") coords '("c")))
(setq currobj (ssadd (entlast) currobj))
(setq coords (list 
(list 2240.5625 678.0723) 
(list 2314.585 678.1223) 
(list 2314.585 678.2993) 
(list 2240.5625 678.1493)))
(apply 'command (append '("pline") coords '("c")))
(setq currobj (ssadd (entlast) currobj))
(setq coords (list 
(list 2240.5625 678.2923) 
(list 2314.585 678.4423) 
(list 2314.585 678.6193) 
(list 2240.5625 678.3693)))
(apply 'command (append '("pline") coords '("c")))
(setq currobj (ssadd (entlast) currobj))
(setq coords (list 
(list 2240.5625 678.5123) 
(list 2314.585 678.7623) 
(list 2314.585 678.9393) 
(list 2240.5625 678.5893)))
(apply 'command (append '("pline") coords '("c")))
(setq currobj (ssadd (entlast) currobj))
(setq coords (list 
(list 2240.5625 678.7323) 
(list 2314.585 679.0823) 
(list 2314.585 679.2593) 
(list 2240.5625 678.8093)))
(apply 'command (append '("pline") coords '("c")))
(setq currobj (ssadd (entlast) currobj))
(setq coords (list 
(list 2240.5625 678.9523) 
(list 2314.585 679.4023) 
(list 2314.585 679.5793) 
(list 2240.5625 679.0293)))
(apply 'command (append '("pline") coords '("c")))
(setq currobj (ssadd (entlast) currobj))
(setq coords (list 
(list 2240.5625 679.1723) 
(list 2314.585 679.7223) 
(list 2314.585 679.8993) 
(list 2240.5625 679.2493)))
(apply 'command (append '("pline") coords '("c")))
(setq currobj (ssadd (entlast) currobj))
(setq coords (list 
(list 2240.5625 679.3923) 
(list 2314.585 680.0423) 
(list 2314.585 680.2193) 
(list 2240.5625 679.4693)))
(apply 'command (append '("pline") coords '("c")))
(setq currobj (ssadd (entlast) currobj))
(setq coords (list 
(list 2239.4375 679.4693) 
(list 2165.415 680.2193) 
(list 2165.415 680.0423) 
(list 2239.4375 679.3923)))
(apply 'command (append '("pline") coords '("c")))
(setq currobj (ssadd (entlast) currobj))
(setq coords (list 
(list 2239.4375 679.2493) 
(list 2165.415 679.8993) 
(list 2165.415 679.7223) 
(list 2239.4375 679.1723)))
(apply 'command (append '("pline") coords '("c")))
(setq currobj (ssadd (entlast) currobj))
(setq coords (list 
(list 2239.4375 679.0293) 
(list 2165.415 679.5793) 
(list 2165.415 679.4023) 
(list 2239.4375 678.9523)))
(apply 'command (append '("pline") coords '("c")))
(setq currobj (ssadd (entlast) currobj))
(setq coords (list 
(list 2239.4375 678.8093) 
(list 2165.415 679.2593) 
(list 2165.415 679.0823) 
(list 2239.4375 678.7323)))
(apply 'command (append '("pline") coords '("c")))
(setq currobj (ssadd (entlast) currobj))
(setq coords (list 
(list 2239.4375 678.5893) 
(list 2165.415 678.9393) 
(list 2165.415 678.7623) 
(list 2239.4375 678.5123)))
(apply 'command (append '("pline") coords '("c")))
(setq currobj (ssadd (entlast) currobj))
(setq coords (list 
(list 2239.4375 678.3693) 
(list 2165.415 678.6193) 
(list 2165.415 678.4423) 
(list 2239.4375 678.2923)))
(apply 'command (append '("pline") coords '("c")))
(setq currobj (ssadd (entlast) currobj))
(setq coords (list 
(list 2239.4375 678.1493) 
(list 2165.415 678.2993) 
(list 2165.415 678.1223) 
(list 2239.4375 678.0723)))
(apply 'command (append '("pline") coords '("c")))
(setq currobj (ssadd (entlast) currobj))
(setq coords (list 
(list 2239.4375 677.9293) 
(list 2165.415 677.9793) 
(list 2165.415 677.8023) 
(list 2239.4375 677.8523)))
(apply 'command (append '("pline") coords '("c")))
(setq currobj (ssadd (entlast) currobj))
(setq coords (list 
(list 2239.4375 677.7093) 
(list 2165.415 677.6593) 
(list 2165.415 677.4823) 
(list 2239.4375 677.6323)))
(apply 'command (append '("pline") coords '("c")))
(setq currobj (ssadd (entlast) currobj))
(setq coords (list 
(list 2239.4375 677.4893) 
(list 2165.415 677.3393) 
(list 2165.415 677.1623) 
(list 2239.4375 677.4123)))
(apply 'command (append '("pline") coords '("c")))
(setq currobj (ssadd (entlast) currobj))
(setq coords (list 
(list 2239.4375 677.2693) 
(list 2165.415 677.0193) 
(list 2165.415 676.8423) 
(list 2239.4375 677.1923)))
(apply 'command (append '("pline") coords '("c")))
(setq currobj (ssadd (entlast) currobj))
(setq coords (list 
(list 2239.4375 677.0493) 
(list 2165.415 676.6993) 
(list 2165.415 676.5223) 
(list 2239.4375 676.9723)))
(apply 'command (append '("pline") coords '("c")))
(setq currobj (ssadd (entlast) currobj))
(setq coords (list 
(list 2239.4375 676.8293) 
(list 2165.415 676.3793) 
(list 2165.415 676.2023) 
(list 2239.4375 676.7523)))
(apply 'command (append '("pline") coords '("c")))
(setq currobj (ssadd (entlast) currobj))
(setq coords (list 
(list 2239.4375 676.6093) 
(list 2165.415 676.0593) 
(list 2165.415 675.8823) 
(list 2239.4375 676.5323)))
(apply 'command (append '("pline") coords '("c")))
(setq currobj (ssadd (entlast) currobj))
(setq coords (list 
(list 2239.4375 676.3893) 
(list 2165.415 675.7393) 
(list 2165.415 675.5623) 
(list 2239.4375 676.3123)))
(apply 'command (append '("pline") coords '("c")))
(setq currobj (ssadd (entlast) currobj))
(command "_layer" "set" "nitride" "")
(command "_layer" "set" "text" "")
(command "_circle" "2239.0625,665.1693" "0.075")
(command "_circle" "2239.0625,665.4693" "0.075")
(command "_circle" "2239.0625,665.7693" "0.075")
(command "_circle" "2239.0625,666.0693" "0.075")
(command "_circle" "2239.0625,666.3693" "0.075")
(command "_circle" "2238.7625,665.1693" "0.075")
(command "_circle" "2238.7625,665.4693" "0.075")
(command "_circle" "2238.7625,665.7693" "0.075")
(command "_circle" "2238.7625,666.0693" "0.075")
(command "_circle" "2238.7625,666.3693" "0.075")
(command "_circle" "2238.4625,665.1693" "0.075")
(command "_circle" "2238.4625,665.4693" "0.075")
(command "_circle" "2238.4625,665.7693" "0.075")
(command "_circle" "2238.4625,666.0693" "0.075")
(command "_circle" "2238.4625,666.3693" "0.075")
(command "_circle" "2238.1625,665.1693" "0.075")
(command "_circle" "2238.1625,665.4693" "0.075")
(command "_circle" "2238.1625,665.7693" "0.075")
(command "_circle" "2238.1625,666.0693" "0.075")
(command "_circle" "2238.1625,666.3693" "0.075")
(command "_circle" "2237.8625,665.1693" "0.075")
(command "_circle" "2237.8625,665.4693" "0.075")
(command "_circle" "2237.8625,665.7693" "0.075")
(command "_circle" "2237.8625,666.0693" "0.075")
(command "_circle" "2237.8625,666.3693" "0.075")
(command "_layer" "set" "nitride" "")
(setq coords (list 
(list 2240.2625 690.6123) 
(list 2240.2625 806.257) 
(list 2239.7375 806.257) 
(list 2239.7375 690.6123)))
(apply 'command (append '("pline") coords '("c")))
(setq currobj (ssadd (entlast) currobj))
(command "_layer" "set" "prebias" "")
(command "_rectangle" "2239.7375,690.6123" "2240.2625,806.257")
(setq currobj (ssadd (entlast) currobj))
(command "_layer" "set" "nitride" "")
(setq coords (list 
(list 2240.2625 806.257) 
(list 2240.5625 816.257) 
(list 2240.5625 816.257) 
(list 2240.5625 817.257) 
(list 2314.585 816.507) 
(list 2314.585 821.45) 
(list 2240.5625 820.7) 
(list 2240.5625 821.7) 
(list 2240.5625 821.7) 
(list 2240.2625 831.7) 
(list 2239.7375 831.7) 
(list 2239.4375 821.7) 
(list 2239.4375 821.7) 
(list 2239.4375 820.7) 
(list 2165.415 821.45) 
(list 2165.415 816.507) 
(list 2239.4375 817.257) 
(list 2239.4375 816.257) 
(list 2239.4375 816.257) 
(list 2239.7375 806.257)))
(apply 'command (append '("pline") coords '("c")))
(setq currobj (ssadd (entlast) currobj))
(command "_layer" "set" "prebias" "")
(setq coords (list 
(list 2239.4375 806.257) 
(list 2239.4375 817.257) 
(list 2165.415 816.507) 
(list 2165.415 821.45) 
(list 2239.4375 820.7) 
(list 2239.4375 831.7) 
(list 2240.5625 831.7) 
(list 2240.5625 820.7) 
(list 2314.585 821.45) 
(list 2314.585 816.507) 
(list 2240.5625 817.257) 
(list 2240.5625 806.257)))
(apply 'command (append '("pline") coords '("c")))
(setq currobj (ssadd (entlast) currobj))
(command "_layer" "set" "nitride" "")
(command "_layer" "set" "fda1" "")
(setq coords (list 
(list 2240.5625 817.4) 
(list 2314.585 816.65) 
(list 2314.585 816.827) 
(list 2240.5625 817.477)))
(apply 'command (append '("pline") coords '("c")))
(setq currobj (ssadd (entlast) currobj))
(setq coords (list 
(list 2240.5625 817.62) 
(list 2314.585 816.97) 
(list 2314.585 817.147) 
(list 2240.5625 817.697)))
(apply 'command (append '("pline") coords '("c")))
(setq currobj (ssadd (entlast) currobj))
(setq coords (list 
(list 2240.5625 817.84) 
(list 2314.585 817.29) 
(list 2314.585 817.467) 
(list 2240.5625 817.917)))
(apply 'command (append '("pline") coords '("c")))
(setq currobj (ssadd (entlast) currobj))
(setq coords (list 
(list 2240.5625 818.06) 
(list 2314.585 817.61) 
(list 2314.585 817.787) 
(list 2240.5625 818.137)))
(apply 'command (append '("pline") coords '("c")))
(setq currobj (ssadd (entlast) currobj))
(setq coords (list 
(list 2240.5625 818.28) 
(list 2314.585 817.93) 
(list 2314.585 818.107) 
(list 2240.5625 818.357)))
(apply 'command (append '("pline") coords '("c")))
(setq currobj (ssadd (entlast) currobj))
(setq coords (list 
(list 2240.5625 818.5) 
(list 2314.585 818.25) 
(list 2314.585 818.427) 
(list 2240.5625 818.577)))
(apply 'command (append '("pline") coords '("c")))
(setq currobj (ssadd (entlast) currobj))
(setq coords (list 
(list 2240.5625 818.72) 
(list 2314.585 818.57) 
(list 2314.585 818.747) 
(list 2240.5625 818.797)))
(apply 'command (append '("pline") coords '("c")))
(setq currobj (ssadd (entlast) currobj))
(setq coords (list 
(list 2240.5625 818.94) 
(list 2314.585 818.89) 
(list 2314.585 819.067) 
(list 2240.5625 819.017)))
(apply 'command (append '("pline") coords '("c")))
(setq currobj (ssadd (entlast) currobj))
(setq coords (list 
(list 2240.5625 819.16) 
(list 2314.585 819.21) 
(list 2314.585 819.387) 
(list 2240.5625 819.237)))
(apply 'command (append '("pline") coords '("c")))
(setq currobj (ssadd (entlast) currobj))
(setq coords (list 
(list 2240.5625 819.38) 
(list 2314.585 819.53) 
(list 2314.585 819.707) 
(list 2240.5625 819.457)))
(apply 'command (append '("pline") coords '("c")))
(setq currobj (ssadd (entlast) currobj))
(setq coords (list 
(list 2240.5625 819.6) 
(list 2314.585 819.85) 
(list 2314.585 820.027) 
(list 2240.5625 819.677)))
(apply 'command (append '("pline") coords '("c")))
(setq currobj (ssadd (entlast) currobj))
(setq coords (list 
(list 2240.5625 819.82) 
(list 2314.585 820.17) 
(list 2314.585 820.347) 
(list 2240.5625 819.897)))
(apply 'command (append '("pline") coords '("c")))
(setq currobj (ssadd (entlast) currobj))
(setq coords (list 
(list 2240.5625 820.04) 
(list 2314.585 820.49) 
(list 2314.585 820.667) 
(list 2240.5625 820.117)))
(apply 'command (append '("pline") coords '("c")))
(setq currobj (ssadd (entlast) currobj))
(setq coords (list 
(list 2240.5625 820.26) 
(list 2314.585 820.81) 
(list 2314.585 820.987) 
(list 2240.5625 820.337)))
(apply 'command (append '("pline") coords '("c")))
(setq currobj (ssadd (entlast) currobj))
(setq coords (list 
(list 2240.5625 820.48) 
(list 2314.585 821.13) 
(list 2314.585 821.307) 
(list 2240.5625 820.557)))
(apply 'command (append '("pline") coords '("c")))
(setq currobj (ssadd (entlast) currobj))
(setq coords (list 
(list 2239.4375 820.557) 
(list 2165.415 821.307) 
(list 2165.415 821.13) 
(list 2239.4375 820.48)))
(apply 'command (append '("pline") coords '("c")))
(setq currobj (ssadd (entlast) currobj))
(setq coords (list 
(list 2239.4375 820.337) 
(list 2165.415 820.987) 
(list 2165.415 820.81) 
(list 2239.4375 820.26)))
(apply 'command (append '("pline") coords '("c")))
(setq currobj (ssadd (entlast) currobj))
(setq coords (list 
(list 2239.4375 820.117) 
(list 2165.415 820.667) 
(list 2165.415 820.49) 
(list 2239.4375 820.04)))
(apply 'command (append '("pline") coords '("c")))
(setq currobj (ssadd (entlast) currobj))
(setq coords (list 
(list 2239.4375 819.897) 
(list 2165.415 820.347) 
(list 2165.415 820.17) 
(list 2239.4375 819.82)))
(apply 'command (append '("pline") coords '("c")))
(setq currobj (ssadd (entlast) currobj))
(setq coords (list 
(list 2239.4375 819.677) 
(list 2165.415 820.027) 
(list 2165.415 819.85) 
(list 2239.4375 819.6)))
(apply 'command (append '("pline") coords '("c")))
(setq currobj (ssadd (entlast) currobj))
(setq coords (list 
(list 2239.4375 819.457) 
(list 2165.415 819.707) 
(list 2165.415 819.53) 
(list 2239.4375 819.38)))
(apply 'command (append '("pline") coords '("c")))
(setq currobj (ssadd (entlast) currobj))
(setq coords (list 
(list 2239.4375 819.237) 
(list 2165.415 819.387) 
(list 2165.415 819.21) 
(list 2239.4375 819.16)))
(apply 'command (append '("pline") coords '("c")))
(setq currobj (ssadd (entlast) currobj))
(setq coords (list 
(list 2239.4375 819.017) 
(list 2165.415 819.067) 
(list 2165.415 818.89) 
(list 2239.4375 818.94)))
(apply 'command (append '("pline") coords '("c")))
(setq currobj (ssadd (entlast) currobj))
(setq coords (list 
(list 2239.4375 818.797) 
(list 2165.415 818.747) 
(list 2165.415 818.57) 
(list 2239.4375 818.72)))
(apply 'command (append '("pline") coords '("c")))
(setq currobj (ssadd (entlast) currobj))
(setq coords (list 
(list 2239.4375 818.577) 
(list 2165.415 818.427) 
(list 2165.415 818.25) 
(list 2239.4375 818.5)))
(apply 'command (append '("pline") coords '("c")))
(setq currobj (ssadd (entlast) currobj))
(setq coords (list 
(list 2239.4375 818.357) 
(list 2165.415 818.107) 
(list 2165.415 817.93) 
(list 2239.4375 818.28)))
(apply 'command (append '("pline") coords '("c")))
(setq currobj (ssadd (entlast) currobj))
(setq coords (list 
(list 2239.4375 818.137) 
(list 2165.415 817.787) 
(list 2165.415 817.61) 
(list 2239.4375 818.06)))
(apply 'command (append '("pline") coords '("c")))
(setq currobj (ssadd (entlast) currobj))
(setq coords (list 
(list 2239.4375 817.917) 
(list 2165.415 817.467) 
(list 2165.415 817.29) 
(list 2239.4375 817.84)))
(apply 'command (append '("pline") coords '("c")))
(setq currobj (ssadd (entlast) currobj))
(setq coords (list 
(list 2239.4375 817.697) 
(list 2165.415 817.147) 
(list 2165.415 816.97) 
(list 2239.4375 817.62)))
(apply 'command (append '("pline") coords '("c")))
(setq currobj (ssadd (entlast) currobj))
(setq coords (list 
(list 2239.4375 817.477) 
(list 2165.415 816.827) 
(list 2165.415 816.65) 
(list 2239.4375 817.4)))
(apply 'command (append '("pline") coords '("c")))
(setq currobj (ssadd (entlast) currobj))
(command "_layer" "set" "nitride" "")
(command "_layer" "set" "text" "")
(command "_circle" "2239.0625,806.257" "0.075")
(command "_circle" "2239.0625,806.557" "0.075")
(command "_circle" "2239.0625,806.857" "0.075")
(command "_circle" "2239.0625,807.157" "0.075")
(command "_circle" "2239.0625,807.457" "0.075")
(command "_circle" "2238.7625,806.257" "0.075")
(command "_circle" "2238.7625,806.557" "0.075")
(command "_circle" "2238.7625,806.857" "0.075")
(command "_circle" "2238.7625,807.157" "0.075")
(command "_circle" "2238.7625,807.457" "0.075")
(command "_circle" "2238.4625,806.257" "0.075")
(command "_circle" "2238.4625,806.557" "0.075")
(command "_circle" "2238.4625,806.857" "0.075")
(command "_circle" "2238.4625,807.157" "0.075")
(command "_circle" "2238.4625,807.457" "0.075")
(command "_circle" "2238.1625,806.257" "0.075")
(command "_circle" "2238.1625,806.557" "0.075")
(command "_circle" "2238.1625,806.857" "0.075")
(command "_circle" "2238.1625,807.157" "0.075")
(command "_circle" "2238.1625,807.457" "0.075")
(command "_circle" "2237.8625,806.257" "0.075")
(command "_circle" "2237.8625,806.557" "0.075")
(command "_circle" "2237.8625,806.857" "0.075")
(command "_circle" "2237.8625,807.157" "0.075")
(command "_circle" "2237.8625,807.457" "0.075")
(command "_layer" "set" "nitride" "")
(setq coords (list 
(list 2240.2625 831.7) 
(list 2240.2625 836.7) 
(list 2239.7375 836.7) 
(list 2239.7375 831.7)))
(apply 'command (append '("pline") coords '("c")))
(setq currobj (ssadd (entlast) currobj))
(command "_layer" "set" "prebias" "")
(command "_rectangle" "2239.7375,831.7" "2240.2625,836.7")
(setq currobj (ssadd (entlast) currobj))
(command "_layer" "set" "nitride" "")
(setq cooledsinglenanobeam7 currobj)
(setq currobj nil)
(setq currobj (ssadd))
; DRAWING PHOTONIC CRYSTAL
(command "_layer" "set" "negYjunc" "")
(setq coords (list 
(list 2240.125 866.7) 
(list 2240 851.7) 
(list 2240 866.7)))
(apply 'command (append '("pline") coords '("c")))
(setq currobj (ssadd (entlast) currobj))
(setq coords (list 
(list 2240.2625 836.7) 
(list 2240.405 866.7) 
(list 2241.112 866.7) 
(list 2241.112 836.7)))
(apply 'command (append '("pline") coords '("c")))
(setq currobj (ssadd (entlast) currobj))
(setq coords (list 
(list 2239.875 866.7) 
(list 2240 851.7) 
(list 2240 866.7)))
(apply 'command (append '("pline") coords '("c")))
(setq currobj (ssadd (entlast) currobj))
(setq coords (list 
(list 2239.7375 836.7) 
(list 2239.595 866.7) 
(list 2238.888 866.7) 
(list 2238.888 836.7)))
(apply 'command (append '("pline") coords '("c")))
(setq currobj (ssadd (entlast) currobj))
(command "_layer" "set" "nitride" "")
(setq yjunction7 currobj)
(setq currobj nil)
(setq currobj (ssadd))
(setq tap7 nil)
(setq tap7 (ssadd))
(command "_layer" "set" "phc" "")
(setq coords (list 
(list 2240 866.7) 
(list 2240.125 866.7) 
(list 2240.125 866.7103) 
(list 2240.125 866.7206) 
(list 2240.125 866.7308) 
(list 2240.125 866.7411) 
(list 2240.125 866.7514) 
(list 2240.125 866.7617) 
(list 2240.125 866.7719) 
(list 2240.125 866.7822) 
(list 2240.125 866.7925) 
(list 2240.125 866.8028) 
(list 2240.125 866.8131) 
(list 2240.125 866.8233) 
(list 2240.125 866.8336) 
(list 2240.125 866.8439) 
(list 2240.125 866.8542) 
(list 2240.125 866.8644) 
(list 2240.125 866.8747) 
(list 2240.125 866.885) 
(list 2240.125 866.8953) 
(list 2240.125 866.9056) 
(list 2240.125 866.9158) 
(list 2240.125 866.9261) 
(list 2240.125 866.9364) 
(list 2240.125 866.9467) 
(list 2240.125 866.9569) 
(list 2240.125 866.9672) 
(list 2240.125 866.9775) 
(list 2240.125 866.9878) 
(list 2240.125 866.9981) 
(list 2240.125 867.0083) 
(list 2240.125 867.0186) 
(list 2240.125 867.0289) 
(list 2240.125 867.0392) 
(list 2240.125 867.0494) 
(list 2240.125 867.0597) 
(list 2240.125 867.07) 
(list 2240 867.07)))
(apply 'command (append '("pline") coords '("c")))
(setq tap7 (ssadd (entlast) tap7))
(command "_mirror" (entlast) "" "2240,900" "2240,901" "No")
(setq tap7 (ssadd (entlast) tap7))
(setq coords (list 
(list 2240.4151 866.7) 
(list 2240.405 866.7) 
(list 2240.4053 866.7103) 
(list 2240.4055 866.7206) 
(list 2240.4057 866.7308) 
(list 2240.4059 866.7411) 
(list 2240.4059 866.7514) 
(list 2240.4059 866.7617) 
(list 2240.4058 866.7719) 
(list 2240.4056 866.7822) 
(list 2240.4052 866.7925) 
(list 2240.4048 866.8028) 
(list 2240.4043 866.8131) 
(list 2240.4038 866.8233) 
(list 2240.4032 866.8336) 
(list 2240.4026 866.8439) 
(list 2240.4021 866.8542) 
(list 2240.4016 866.8644) 
(list 2240.4012 866.8747) 
(list 2240.4009 866.885) 
(list 2240.4007 866.8953) 
(list 2240.4007 866.9056) 
(list 2240.4009 866.9158) 
(list 2240.4013 866.9261) 
(list 2240.4018 866.9364) 
(list 2240.4026 866.9467) 
(list 2240.4035 866.9569) 
(list 2240.4045 866.9672) 
(list 2240.4057 866.9775) 
(list 2240.407 866.9878) 
(list 2240.4083 866.9981) 
(list 2240.4096 867.0083) 
(list 2240.4109 867.0186) 
(list 2240.412 867.0289) 
(list 2240.4131 867.0392) 
(list 2240.414 867.0494) 
(list 2240.4147 867.0597) 
(list 2240.4151 867.07) 
(list 2240.4151 867.07)))
(apply 'command (append '("pline") coords '("c")))
(setq tap7 (ssadd (entlast) tap7))
(command "_mirror" (entlast) "" "2240,900" "2240,901" "No")
(setq tap7 (ssadd (entlast) tap7))
(setq coords (list 
(list 2241.112 866.7) 
(list 2240.4151 866.7) 
(list 2240.4151 866.7103) 
(list 2240.4151 866.7206) 
(list 2240.4151 866.7308) 
(list 2240.4151 866.7411) 
(list 2240.4151 866.7514) 
(list 2240.4151 866.7617) 
(list 2240.4151 866.7719) 
(list 2240.4151 866.7822) 
(list 2240.4151 866.7925) 
(list 2240.4151 866.8028) 
(list 2240.4151 866.8131) 
(list 2240.4151 866.8233) 
(list 2240.4151 866.8336) 
(list 2240.4151 866.8439) 
(list 2240.4151 866.8542) 
(list 2240.4151 866.8644) 
(list 2240.4151 866.8747) 
(list 2240.4151 866.885) 
(list 2240.4151 866.8953) 
(list 2240.4151 866.9056) 
(list 2240.4151 866.9158) 
(list 2240.4151 866.9261) 
(list 2240.4151 866.9364) 
(list 2240.4151 866.9467) 
(list 2240.4151 866.9569) 
(list 2240.4151 866.9672) 
(list 2240.4151 866.9775) 
(list 2240.4151 866.9878) 
(list 2240.4151 866.9981) 
(list 2240.4151 867.0083) 
(list 2240.4151 867.0186) 
(list 2240.4151 867.0289) 
(list 2240.4151 867.0392) 
(list 2240.4151 867.0494) 
(list 2240.4151 867.0597) 
(list 2240.4151 867.07) 
(list 2241.112 867.07)))
(apply 'command (append '("pline") coords '("c")))
(setq tap7 (ssadd (entlast) tap7))
(command "_mirror" (entlast) "" "2240,900" "2240,901" "No")
(setq tap7 (ssadd (entlast) tap7))
(setq coords (list 
(list 2240 867.07) 
(list 2240.125 867.07) 
(list 2240.125 867.0803) 
(list 2240.125 867.0906) 
(list 2240.125 867.1008) 
(list 2240.125 867.1111) 
(list 2240.125 867.1214) 
(list 2240.125 867.1317) 
(list 2240.125 867.1419) 
(list 2240.125 867.1522) 
(list 2240.125 867.1625) 
(list 2240.125 867.1728) 
(list 2240.125 867.1831) 
(list 2240.125 867.1933) 
(list 2240.125 867.2036) 
(list 2240.125 867.2139) 
(list 2240.125 867.2242) 
(list 2240.125 867.2344) 
(list 2240.125 867.2447) 
(list 2240.125 867.255) 
(list 2240.125 867.2653) 
(list 2240.125 867.2756) 
(list 2240.125 867.2858) 
(list 2240.125 867.2961) 
(list 2240.125 867.3064) 
(list 2240.125 867.3167) 
(list 2240.125 867.3269) 
(list 2240.125 867.3372) 
(list 2240.125 867.3475) 
(list 2240.125 867.3578) 
(list 2240.125 867.3681) 
(list 2240.125 867.3783) 
(list 2240.125 867.3886) 
(list 2240.125 867.3989) 
(list 2240.125 867.4092) 
(list 2240.125 867.4194) 
(list 2240.125 867.4297) 
(list 2240.125 867.44) 
(list 2240 867.44)))
(apply 'command (append '("pline") coords '("c")))
(setq tap7 (ssadd (entlast) tap7))
(command "_mirror" (entlast) "" "2240,900" "2240,901" "No")
(setq tap7 (ssadd (entlast) tap7))
(setq coords (list 
(list 2240.4251 867.07) 
(list 2240.4151 867.07) 
(list 2240.4152 867.0803) 
(list 2240.415 867.0906) 
(list 2240.4146 867.1008) 
(list 2240.4138 867.1111) 
(list 2240.4127 867.1214) 
(list 2240.4114 867.1317) 
(list 2240.4098 867.1419) 
(list 2240.4081 867.1522) 
(list 2240.4062 867.1625) 
(list 2240.4042 867.1728) 
(list 2240.4021 867.1831) 
(list 2240.4002 867.1933) 
(list 2240.3983 867.2036) 
(list 2240.3966 867.2139) 
(list 2240.3951 867.2242) 
(list 2240.394 867.2344) 
(list 2240.3931 867.2447) 
(list 2240.3927 867.255) 
(list 2240.3927 867.2653) 
(list 2240.3931 867.2756) 
(list 2240.394 867.2858) 
(list 2240.3952 867.2961) 
(list 2240.3969 867.3064) 
(list 2240.3989 867.3167) 
(list 2240.4013 867.3269) 
(list 2240.4039 867.3372) 
(list 2240.4066 867.3475) 
(list 2240.4095 867.3578) 
(list 2240.4123 867.3681) 
(list 2240.4151 867.3783) 
(list 2240.4177 867.3886) 
(list 2240.42 867.3989) 
(list 2240.4219 867.4092) 
(list 2240.4235 867.4194) 
(list 2240.4246 867.4297) 
(list 2240.4251 867.44) 
(list 2240.4251 867.44)))
(apply 'command (append '("pline") coords '("c")))
(setq tap7 (ssadd (entlast) tap7))
(command "_mirror" (entlast) "" "2240,900" "2240,901" "No")
(setq tap7 (ssadd (entlast) tap7))
(setq coords (list 
(list 2241.112 867.07) 
(list 2240.4251 867.07) 
(list 2240.4251 867.0803) 
(list 2240.4251 867.0906) 
(list 2240.4251 867.1008) 
(list 2240.4251 867.1111) 
(list 2240.4251 867.1214) 
(list 2240.4251 867.1317) 
(list 2240.4251 867.1419) 
(list 2240.4251 867.1522) 
(list 2240.4251 867.1625) 
(list 2240.4251 867.1728) 
(list 2240.4251 867.1831) 
(list 2240.4251 867.1933) 
(list 2240.4251 867.2036) 
(list 2240.4251 867.2139) 
(list 2240.4251 867.2242) 
(list 2240.4251 867.2344) 
(list 2240.4251 867.2447) 
(list 2240.4251 867.255) 
(list 2240.4251 867.2653) 
(list 2240.4251 867.2756) 
(list 2240.4251 867.2858) 
(list 2240.4251 867.2961) 
(list 2240.4251 867.3064) 
(list 2240.4251 867.3167) 
(list 2240.4251 867.3269) 
(list 2240.4251 867.3372) 
(list 2240.4251 867.3475) 
(list 2240.4251 867.3578) 
(list 2240.4251 867.3681) 
(list 2240.4251 867.3783) 
(list 2240.4251 867.3886) 
(list 2240.4251 867.3989) 
(list 2240.4251 867.4092) 
(list 2240.4251 867.4194) 
(list 2240.4251 867.4297) 
(list 2240.4251 867.44) 
(list 2241.112 867.44)))
(apply 'command (append '("pline") coords '("c")))
(setq tap7 (ssadd (entlast) tap7))
(command "_mirror" (entlast) "" "2240,900" "2240,901" "No")
(setq tap7 (ssadd (entlast) tap7))
(setq coords (list 
(list 2240 867.44) 
(list 2240.125 867.44) 
(list 2240.125 867.4503) 
(list 2240.125 867.4606) 
(list 2240.125 867.4708) 
(list 2240.125 867.4811) 
(list 2240.125 867.4914) 
(list 2240.125 867.5017) 
(list 2240.125 867.5119) 
(list 2240.125 867.5222) 
(list 2240.125 867.5325) 
(list 2240.125 867.5428) 
(list 2240.125 867.5531) 
(list 2240.125 867.5633) 
(list 2240.125 867.5736) 
(list 2240.125 867.5839) 
(list 2240.125 867.5942) 
(list 2240.125 867.6044) 
(list 2240.125 867.6147) 
(list 2240.125 867.625) 
(list 2240.125 867.6353) 
(list 2240.125 867.6456) 
(list 2240.125 867.6558) 
(list 2240.125 867.6661) 
(list 2240.125 867.6764) 
(list 2240.125 867.6867) 
(list 2240.125 867.6969) 
(list 2240.125 867.7072) 
(list 2240.125 867.7175) 
(list 2240.125 867.7278) 
(list 2240.125 867.7381) 
(list 2240.125 867.7483) 
(list 2240.125 867.7586) 
(list 2240.125 867.7689) 
(list 2240.125 867.7792) 
(list 2240.125 867.7894) 
(list 2240.125 867.7997) 
(list 2240.125 867.81) 
(list 2240 867.81)))
(apply 'command (append '("pline") coords '("c")))
(setq tap7 (ssadd (entlast) tap7))
(command "_mirror" (entlast) "" "2240,900" "2240,901" "No")
(setq tap7 (ssadd (entlast) tap7))
(setq coords (list 
(list 2240.4352 867.44) 
(list 2240.4251 867.44) 
(list 2240.4251 867.4503) 
(list 2240.4246 867.4606) 
(list 2240.4234 867.4708) 
(list 2240.4217 867.4811) 
(list 2240.4196 867.4914) 
(list 2240.4169 867.5017) 
(list 2240.4139 867.5119) 
(list 2240.4106 867.5222) 
(list 2240.4071 867.5325) 
(list 2240.4035 867.5428) 
(list 2240.3999 867.5531) 
(list 2240.3965 867.5633) 
(list 2240.3933 867.5736) 
(list 2240.3905 867.5839) 
(list 2240.3881 867.5942) 
(list 2240.3863 867.6044) 
(list 2240.3851 867.6147) 
(list 2240.3845 867.625) 
(list 2240.3846 867.6353) 
(list 2240.3855 867.6456) 
(list 2240.387 867.6558) 
(list 2240.3892 867.6661) 
(list 2240.392 867.6764) 
(list 2240.3953 867.6867) 
(list 2240.3991 867.6969) 
(list 2240.4032 867.7072) 
(list 2240.4076 867.7175) 
(list 2240.412 867.7278) 
(list 2240.4164 867.7381) 
(list 2240.4206 867.7483) 
(list 2240.4245 867.7586) 
(list 2240.4279 867.7689) 
(list 2240.4308 867.7792) 
(list 2240.433 867.7894) 
(list 2240.4345 867.7997) 
(list 2240.4352 867.81) 
(list 2240.4352 867.81)))
(apply 'command (append '("pline") coords '("c")))
(setq tap7 (ssadd (entlast) tap7))
(command "_mirror" (entlast) "" "2240,900" "2240,901" "No")
(setq tap7 (ssadd (entlast) tap7))
(setq coords (list 
(list 2241.112 867.44) 
(list 2240.4352 867.44) 
(list 2240.4352 867.4503) 
(list 2240.4352 867.4606) 
(list 2240.4352 867.4708) 
(list 2240.4352 867.4811) 
(list 2240.4352 867.4914) 
(list 2240.4352 867.5017) 
(list 2240.4352 867.5119) 
(list 2240.4352 867.5222) 
(list 2240.4352 867.5325) 
(list 2240.4352 867.5428) 
(list 2240.4352 867.5531) 
(list 2240.4352 867.5633) 
(list 2240.4352 867.5736) 
(list 2240.4352 867.5839) 
(list 2240.4352 867.5942) 
(list 2240.4352 867.6044) 
(list 2240.4352 867.6147) 
(list 2240.4352 867.625) 
(list 2240.4352 867.6353) 
(list 2240.4352 867.6456) 
(list 2240.4352 867.6558) 
(list 2240.4352 867.6661) 
(list 2240.4352 867.6764) 
(list 2240.4352 867.6867) 
(list 2240.4352 867.6969) 
(list 2240.4352 867.7072) 
(list 2240.4352 867.7175) 
(list 2240.4352 867.7278) 
(list 2240.4352 867.7381) 
(list 2240.4352 867.7483) 
(list 2240.4352 867.7586) 
(list 2240.4352 867.7689) 
(list 2240.4352 867.7792) 
(list 2240.4352 867.7894) 
(list 2240.4352 867.7997) 
(list 2240.4352 867.81) 
(list 2241.112 867.81)))
(apply 'command (append '("pline") coords '("c")))
(setq tap7 (ssadd (entlast) tap7))
(command "_mirror" (entlast) "" "2240,900" "2240,901" "No")
(setq tap7 (ssadd (entlast) tap7))
(setq coords (list 
(list 2240 867.81) 
(list 2240.125 867.81) 
(list 2240.125 867.8203) 
(list 2240.125 867.8306) 
(list 2240.125 867.8408) 
(list 2240.125 867.8511) 
(list 2240.125 867.8614) 
(list 2240.125 867.8717) 
(list 2240.125 867.8819) 
(list 2240.125 867.8922) 
(list 2240.125 867.9025) 
(list 2240.125 867.9128) 
(list 2240.125 867.9231) 
(list 2240.125 867.9333) 
(list 2240.125 867.9436) 
(list 2240.125 867.9539) 
(list 2240.125 867.9642) 
(list 2240.125 867.9744) 
(list 2240.125 867.9847) 
(list 2240.125 867.995) 
(list 2240.125 868.0053) 
(list 2240.125 868.0156) 
(list 2240.125 868.0258) 
(list 2240.125 868.0361) 
(list 2240.125 868.0464) 
(list 2240.125 868.0567) 
(list 2240.125 868.0669) 
(list 2240.125 868.0772) 
(list 2240.125 868.0875) 
(list 2240.125 868.0978) 
(list 2240.125 868.1081) 
(list 2240.125 868.1183) 
(list 2240.125 868.1286) 
(list 2240.125 868.1389) 
(list 2240.125 868.1492) 
(list 2240.125 868.1594) 
(list 2240.125 868.1697) 
(list 2240.125 868.18) 
(list 2240 868.18)))
(apply 'command (append '("pline") coords '("c")))
(setq tap7 (ssadd (entlast) tap7))
(command "_mirror" (entlast) "" "2240,900" "2240,901" "No")
(setq tap7 (ssadd (entlast) tap7))
(setq coords (list 
(list 2240.4453 867.81) 
(list 2240.4352 867.81) 
(list 2240.4351 867.8203) 
(list 2240.4341 867.8306) 
(list 2240.4323 867.8408) 
(list 2240.4297 867.8511) 
(list 2240.4264 867.8614) 
(list 2240.4224 867.8717) 
(list 2240.418 867.8819) 
(list 2240.4131 867.8922) 
(list 2240.408 867.9025) 
(list 2240.4029 867.9128) 
(list 2240.3978 867.9231) 
(list 2240.3929 867.9333) 
(list 2240.3884 867.9436) 
(list 2240.3845 867.9539) 
(list 2240.3812 867.9642) 
(list 2240.3787 867.9744) 
(list 2240.377 867.9847) 
(list 2240.3763 867.995) 
(list 2240.3766 868.0053) 
(list 2240.3778 868.0156) 
(list 2240.38 868.0258) 
(list 2240.3831 868.0361) 
(list 2240.387 868.0464) 
(list 2240.3917 868.0567) 
(list 2240.3969 868.0669) 
(list 2240.4026 868.0772) 
(list 2240.4085 868.0875) 
(list 2240.4145 868.0978) 
(list 2240.4204 868.1081) 
(list 2240.4261 868.1183) 
(list 2240.4313 868.1286) 
(list 2240.4358 868.1389) 
(list 2240.4396 868.1492) 
(list 2240.4425 868.1594) 
(list 2240.4444 868.1697) 
(list 2240.4453 868.18) 
(list 2240.4453 868.18)))
(apply 'command (append '("pline") coords '("c")))
(setq tap7 (ssadd (entlast) tap7))
(command "_mirror" (entlast) "" "2240,900" "2240,901" "No")
(setq tap7 (ssadd (entlast) tap7))
(setq coords (list 
(list 2241.112 867.81) 
(list 2240.4453 867.81) 
(list 2240.4453 867.8203) 
(list 2240.4453 867.8306) 
(list 2240.4453 867.8408) 
(list 2240.4453 867.8511) 
(list 2240.4453 867.8614) 
(list 2240.4453 867.8717) 
(list 2240.4453 867.8819) 
(list 2240.4453 867.8922) 
(list 2240.4453 867.9025) 
(list 2240.4453 867.9128) 
(list 2240.4453 867.9231) 
(list 2240.4453 867.9333) 
(list 2240.4453 867.9436) 
(list 2240.4453 867.9539) 
(list 2240.4453 867.9642) 
(list 2240.4453 867.9744) 
(list 2240.4453 867.9847) 
(list 2240.4453 867.995) 
(list 2240.4453 868.0053) 
(list 2240.4453 868.0156) 
(list 2240.4453 868.0258) 
(list 2240.4453 868.0361) 
(list 2240.4453 868.0464) 
(list 2240.4453 868.0567) 
(list 2240.4453 868.0669) 
(list 2240.4453 868.0772) 
(list 2240.4453 868.0875) 
(list 2240.4453 868.0978) 
(list 2240.4453 868.1081) 
(list 2240.4453 868.1183) 
(list 2240.4453 868.1286) 
(list 2240.4453 868.1389) 
(list 2240.4453 868.1492) 
(list 2240.4453 868.1594) 
(list 2240.4453 868.1697) 
(list 2240.4453 868.18) 
(list 2241.112 868.18)))
(apply 'command (append '("pline") coords '("c")))
(setq tap7 (ssadd (entlast) tap7))
(command "_mirror" (entlast) "" "2240,900" "2240,901" "No")
(setq tap7 (ssadd (entlast) tap7))
(setq coords (list 
(list 2240 868.18) 
(list 2240.125 868.18) 
(list 2240.125 868.1903) 
(list 2240.125 868.2006) 
(list 2240.125 868.2108) 
(list 2240.125 868.2211) 
(list 2240.125 868.2314) 
(list 2240.125 868.2417) 
(list 2240.125 868.2519) 
(list 2240.125 868.2622) 
(list 2240.125 868.2725) 
(list 2240.125 868.2828) 
(list 2240.125 868.2931) 
(list 2240.125 868.3033) 
(list 2240.125 868.3136) 
(list 2240.125 868.3239) 
(list 2240.125 868.3342) 
(list 2240.125 868.3444) 
(list 2240.125 868.3547) 
(list 2240.125 868.365) 
(list 2240.125 868.3753) 
(list 2240.125 868.3856) 
(list 2240.125 868.3958) 
(list 2240.125 868.4061) 
(list 2240.125 868.4164) 
(list 2240.125 868.4267) 
(list 2240.125 868.4369) 
(list 2240.125 868.4472) 
(list 2240.125 868.4575) 
(list 2240.125 868.4678) 
(list 2240.125 868.4781) 
(list 2240.125 868.4883) 
(list 2240.125 868.4986) 
(list 2240.125 868.5089) 
(list 2240.125 868.5192) 
(list 2240.125 868.5294) 
(list 2240.125 868.5397) 
(list 2240.125 868.55) 
(list 2240 868.55)))
(apply 'command (append '("pline") coords '("c")))
(setq tap7 (ssadd (entlast) tap7))
(command "_mirror" (entlast) "" "2240,900" "2240,901" "No")
(setq tap7 (ssadd (entlast) tap7))
(setq coords (list 
(list 2240.4553 868.18) 
(list 2240.4453 868.18) 
(list 2240.445 868.1903) 
(list 2240.4436 868.2006) 
(list 2240.4411 868.2108) 
(list 2240.4376 868.2211) 
(list 2240.4332 868.2314) 
(list 2240.4279 868.2417) 
(list 2240.422 868.2519) 
(list 2240.4156 868.2622) 
(list 2240.409 868.2725) 
(list 2240.4022 868.2828) 
(list 2240.3956 868.2931) 
(list 2240.3893 868.3033) 
(list 2240.3835 868.3136) 
(list 2240.3784 868.3239) 
(list 2240.3742 868.3342) 
(list 2240.371 868.3444) 
(list 2240.3689 868.3547) 
(list 2240.3681 868.365) 
(list 2240.3685 868.3753) 
(list 2240.3702 868.3856) 
(list 2240.373 868.3958) 
(list 2240.377 868.4061) 
(list 2240.3821 868.4164) 
(list 2240.388 868.4267) 
(list 2240.3947 868.4369) 
(list 2240.4019 868.4472) 
(list 2240.4094 868.4575) 
(list 2240.417 868.4678) 
(list 2240.4245 868.4781) 
(list 2240.4316 868.4883) 
(list 2240.4381 868.4986) 
(list 2240.4438 868.5089) 
(list 2240.4485 868.5192) 
(list 2240.452 868.5294) 
(list 2240.4544 868.5397) 
(list 2240.4553 868.55) 
(list 2240.4553 868.55)))
(apply 'command (append '("pline") coords '("c")))
(setq tap7 (ssadd (entlast) tap7))
(command "_mirror" (entlast) "" "2240,900" "2240,901" "No")
(setq tap7 (ssadd (entlast) tap7))
(setq coords (list 
(list 2241.112 868.18) 
(list 2240.4553 868.18) 
(list 2240.4553 868.1903) 
(list 2240.4553 868.2006) 
(list 2240.4553 868.2108) 
(list 2240.4553 868.2211) 
(list 2240.4553 868.2314) 
(list 2240.4553 868.2417) 
(list 2240.4553 868.2519) 
(list 2240.4553 868.2622) 
(list 2240.4553 868.2725) 
(list 2240.4553 868.2828) 
(list 2240.4553 868.2931) 
(list 2240.4553 868.3033) 
(list 2240.4553 868.3136) 
(list 2240.4553 868.3239) 
(list 2240.4553 868.3342) 
(list 2240.4553 868.3444) 
(list 2240.4553 868.3547) 
(list 2240.4553 868.365) 
(list 2240.4553 868.3753) 
(list 2240.4553 868.3856) 
(list 2240.4553 868.3958) 
(list 2240.4553 868.4061) 
(list 2240.4553 868.4164) 
(list 2240.4553 868.4267) 
(list 2240.4553 868.4369) 
(list 2240.4553 868.4472) 
(list 2240.4553 868.4575) 
(list 2240.4553 868.4678) 
(list 2240.4553 868.4781) 
(list 2240.4553 868.4883) 
(list 2240.4553 868.4986) 
(list 2240.4553 868.5089) 
(list 2240.4553 868.5192) 
(list 2240.4553 868.5294) 
(list 2240.4553 868.5397) 
(list 2240.4553 868.55) 
(list 2241.112 868.55)))
(apply 'command (append '("pline") coords '("c")))
(setq tap7 (ssadd (entlast) tap7))
(command "_mirror" (entlast) "" "2240,900" "2240,901" "No")
(setq tap7 (ssadd (entlast) tap7))
(setq coords (list 
(list 2240 868.55) 
(list 2240.125 868.55) 
(list 2240.125 868.5603) 
(list 2240.125 868.5706) 
(list 2240.125 868.5808) 
(list 2240.125 868.5911) 
(list 2240.125 868.6014) 
(list 2240.125 868.6117) 
(list 2240.125 868.6219) 
(list 2240.125 868.6322) 
(list 2240.125 868.6425) 
(list 2240.125 868.6528) 
(list 2240.125 868.6631) 
(list 2240.125 868.6733) 
(list 2240.125 868.6836) 
(list 2240.125 868.6939) 
(list 2240.125 868.7042) 
(list 2240.125 868.7144) 
(list 2240.125 868.7247) 
(list 2240.125 868.735) 
(list 2240.125 868.7453) 
(list 2240.125 868.7556) 
(list 2240.125 868.7658) 
(list 2240.125 868.7761) 
(list 2240.125 868.7864) 
(list 2240.125 868.7967) 
(list 2240.125 868.8069) 
(list 2240.125 868.8172) 
(list 2240.125 868.8275) 
(list 2240.125 868.8378) 
(list 2240.125 868.8481) 
(list 2240.125 868.8583) 
(list 2240.125 868.8686) 
(list 2240.125 868.8789) 
(list 2240.125 868.8892) 
(list 2240.125 868.8994) 
(list 2240.125 868.9097) 
(list 2240.125 868.92) 
(list 2240 868.92)))
(apply 'command (append '("pline") coords '("c")))
(setq tap7 (ssadd (entlast) tap7))
(command "_mirror" (entlast) "" "2240,900" "2240,901" "No")
(setq tap7 (ssadd (entlast) tap7))
(setq coords (list 
(list 2240.4654 868.55) 
(list 2240.4553 868.55) 
(list 2240.4549 868.5603) 
(list 2240.4531 868.5706) 
(list 2240.45 868.5808) 
(list 2240.4455 868.5911) 
(list 2240.44 868.6014) 
(list 2240.4334 868.6117) 
(list 2240.4261 868.6219) 
(list 2240.4182 868.6322) 
(list 2240.4099 868.6425) 
(list 2240.4016 868.6528) 
(list 2240.3934 868.6631) 
(list 2240.3856 868.6733) 
(list 2240.3785 868.6836) 
(list 2240.3723 868.6939) 
(list 2240.3672 868.7042) 
(list 2240.3634 868.7144) 
(list 2240.3609 868.7247) 
(list 2240.3599 868.735) 
(list 2240.3604 868.7453) 
(list 2240.3625 868.7556) 
(list 2240.366 868.7658) 
(list 2240.371 868.7761) 
(list 2240.3772 868.7864) 
(list 2240.3844 868.7967) 
(list 2240.3925 868.8069) 
(list 2240.4013 868.8172) 
(list 2240.4104 868.8275) 
(list 2240.4196 868.8378) 
(list 2240.4286 868.8481) 
(list 2240.4371 868.8583) 
(list 2240.4449 868.8686) 
(list 2240.4517 868.8789) 
(list 2240.4573 868.8892) 
(list 2240.4616 868.8994) 
(list 2240.4643 868.9097) 
(list 2240.4654 868.92) 
(list 2240.4654 868.92)))
(apply 'command (append '("pline") coords '("c")))
(setq tap7 (ssadd (entlast) tap7))
(command "_mirror" (entlast) "" "2240,900" "2240,901" "No")
(setq tap7 (ssadd (entlast) tap7))
(setq coords (list 
(list 2241.112 868.55) 
(list 2240.4654 868.55) 
(list 2240.4654 868.5603) 
(list 2240.4654 868.5706) 
(list 2240.4654 868.5808) 
(list 2240.4654 868.5911) 
(list 2240.4654 868.6014) 
(list 2240.4654 868.6117) 
(list 2240.4654 868.6219) 
(list 2240.4654 868.6322) 
(list 2240.4654 868.6425) 
(list 2240.4654 868.6528) 
(list 2240.4654 868.6631) 
(list 2240.4654 868.6733) 
(list 2240.4654 868.6836) 
(list 2240.4654 868.6939) 
(list 2240.4654 868.7042) 
(list 2240.4654 868.7144) 
(list 2240.4654 868.7247) 
(list 2240.4654 868.735) 
(list 2240.4654 868.7453) 
(list 2240.4654 868.7556) 
(list 2240.4654 868.7658) 
(list 2240.4654 868.7761) 
(list 2240.4654 868.7864) 
(list 2240.4654 868.7967) 
(list 2240.4654 868.8069) 
(list 2240.4654 868.8172) 
(list 2240.4654 868.8275) 
(list 2240.4654 868.8378) 
(list 2240.4654 868.8481) 
(list 2240.4654 868.8583) 
(list 2240.4654 868.8686) 
(list 2240.4654 868.8789) 
(list 2240.4654 868.8892) 
(list 2240.4654 868.8994) 
(list 2240.4654 868.9097) 
(list 2240.4654 868.92) 
(list 2241.112 868.92)))
(apply 'command (append '("pline") coords '("c")))
(setq tap7 (ssadd (entlast) tap7))
(command "_mirror" (entlast) "" "2240,900" "2240,901" "No")
(setq tap7 (ssadd (entlast) tap7))
(setq coords (list 
(list 2240 868.92) 
(list 2240.125 868.92) 
(list 2240.125 868.9303) 
(list 2240.125 868.9406) 
(list 2240.125 868.9508) 
(list 2240.125 868.9611) 
(list 2240.125 868.9714) 
(list 2240.125 868.9817) 
(list 2240.125 868.9919) 
(list 2240.125 869.0022) 
(list 2240.125 869.0125) 
(list 2240.125 869.0228) 
(list 2240.125 869.0331) 
(list 2240.125 869.0433) 
(list 2240.125 869.0536) 
(list 2240.125 869.0639) 
(list 2240.125 869.0742) 
(list 2240.125 869.0844) 
(list 2240.125 869.0947) 
(list 2240.125 869.105) 
(list 2240.125 869.1153) 
(list 2240.125 869.1256) 
(list 2240.125 869.1358) 
(list 2240.125 869.1461) 
(list 2240.125 869.1564) 
(list 2240.125 869.1667) 
(list 2240.125 869.1769) 
(list 2240.125 869.1872) 
(list 2240.125 869.1975) 
(list 2240.125 869.2078) 
(list 2240.125 869.2181) 
(list 2240.125 869.2283) 
(list 2240.125 869.2386) 
(list 2240.125 869.2489) 
(list 2240.125 869.2592) 
(list 2240.125 869.2694) 
(list 2240.125 869.2797) 
(list 2240.125 869.29) 
(list 2240 869.29)))
(apply 'command (append '("pline") coords '("c")))
(setq tap7 (ssadd (entlast) tap7))
(command "_mirror" (entlast) "" "2240,900" "2240,901" "No")
(setq tap7 (ssadd (entlast) tap7))
(setq coords (list 
(list 2240.4755 868.92) 
(list 2240.4654 868.92) 
(list 2240.4648 868.9303) 
(list 2240.4626 868.9406) 
(list 2240.4588 868.9508) 
(list 2240.4535 868.9611) 
(list 2240.4468 868.9714) 
(list 2240.4389 868.9817) 
(list 2240.4301 868.9919) 
(list 2240.4207 869.0022) 
(list 2240.4108 869.0125) 
(list 2240.4009 869.0228) 
(list 2240.3912 869.0331) 
(list 2240.382 869.0433) 
(list 2240.3736 869.0536) 
(list 2240.3663 869.0639) 
(list 2240.3602 869.0742) 
(list 2240.3557 869.0844) 
(list 2240.3528 869.0947) 
(list 2240.3517 869.105) 
(list 2240.3524 869.1153) 
(list 2240.3549 869.1256) 
(list 2240.3591 869.1358) 
(list 2240.3649 869.1461) 
(list 2240.3722 869.1564) 
(list 2240.3808 869.1667) 
(list 2240.3903 869.1769) 
(list 2240.4006 869.1872) 
(list 2240.4113 869.1975) 
(list 2240.4221 869.2078) 
(list 2240.4326 869.2181) 
(list 2240.4426 869.2283) 
(list 2240.4517 869.2386) 
(list 2240.4596 869.2489) 
(list 2240.4662 869.2592) 
(list 2240.4711 869.2694) 
(list 2240.4742 869.2797) 
(list 2240.4755 869.29) 
(list 2240.4755 869.29)))
(apply 'command (append '("pline") coords '("c")))
(setq tap7 (ssadd (entlast) tap7))
(command "_mirror" (entlast) "" "2240,900" "2240,901" "No")
(setq tap7 (ssadd (entlast) tap7))
(setq coords (list 
(list 2241.112 868.92) 
(list 2240.4755 868.92) 
(list 2240.4755 868.9303) 
(list 2240.4755 868.9406) 
(list 2240.4755 868.9508) 
(list 2240.4755 868.9611) 
(list 2240.4755 868.9714) 
(list 2240.4755 868.9817) 
(list 2240.4755 868.9919) 
(list 2240.4755 869.0022) 
(list 2240.4755 869.0125) 
(list 2240.4755 869.0228) 
(list 2240.4755 869.0331) 
(list 2240.4755 869.0433) 
(list 2240.4755 869.0536) 
(list 2240.4755 869.0639) 
(list 2240.4755 869.0742) 
(list 2240.4755 869.0844) 
(list 2240.4755 869.0947) 
(list 2240.4755 869.105) 
(list 2240.4755 869.1153) 
(list 2240.4755 869.1256) 
(list 2240.4755 869.1358) 
(list 2240.4755 869.1461) 
(list 2240.4755 869.1564) 
(list 2240.4755 869.1667) 
(list 2240.4755 869.1769) 
(list 2240.4755 869.1872) 
(list 2240.4755 869.1975) 
(list 2240.4755 869.2078) 
(list 2240.4755 869.2181) 
(list 2240.4755 869.2283) 
(list 2240.4755 869.2386) 
(list 2240.4755 869.2489) 
(list 2240.4755 869.2592) 
(list 2240.4755 869.2694) 
(list 2240.4755 869.2797) 
(list 2240.4755 869.29) 
(list 2241.112 869.29)))
(apply 'command (append '("pline") coords '("c")))
(setq tap7 (ssadd (entlast) tap7))
(command "_mirror" (entlast) "" "2240,900" "2240,901" "No")
(setq tap7 (ssadd (entlast) tap7))
(setq coords (list 
(list 2240 869.29) 
(list 2240.125 869.29) 
(list 2240.125 869.3003) 
(list 2240.125 869.3106) 
(list 2240.125 869.3208) 
(list 2240.125 869.3311) 
(list 2240.125 869.3414) 
(list 2240.125 869.3517) 
(list 2240.125 869.3619) 
(list 2240.125 869.3722) 
(list 2240.125 869.3825) 
(list 2240.125 869.3928) 
(list 2240.125 869.4031) 
(list 2240.125 869.4133) 
(list 2240.125 869.4236) 
(list 2240.125 869.4339) 
(list 2240.125 869.4442) 
(list 2240.125 869.4544) 
(list 2240.125 869.4647) 
(list 2240.125 869.475) 
(list 2240.125 869.4853) 
(list 2240.125 869.4956) 
(list 2240.125 869.5058) 
(list 2240.125 869.5161) 
(list 2240.125 869.5264) 
(list 2240.125 869.5367) 
(list 2240.125 869.5469) 
(list 2240.125 869.5572) 
(list 2240.125 869.5675) 
(list 2240.125 869.5778) 
(list 2240.125 869.5881) 
(list 2240.125 869.5983) 
(list 2240.125 869.6086) 
(list 2240.125 869.6189) 
(list 2240.125 869.6292) 
(list 2240.125 869.6394) 
(list 2240.125 869.6497) 
(list 2240.125 869.66) 
(list 2240 869.66)))
(apply 'command (append '("pline") coords '("c")))
(setq tap7 (ssadd (entlast) tap7))
(command "_mirror" (entlast) "" "2240,900" "2240,901" "No")
(setq tap7 (ssadd (entlast) tap7))
(setq coords (list 
(list 2240.4855 869.29) 
(list 2240.4755 869.29) 
(list 2240.4748 869.3003) 
(list 2240.4721 869.3106) 
(list 2240.4676 869.3208) 
(list 2240.4614 869.3311) 
(list 2240.4536 869.3414) 
(list 2240.4444 869.3517) 
(list 2240.4342 869.3619) 
(list 2240.4232 869.3722) 
(list 2240.4118 869.3825) 
(list 2240.4003 869.3928) 
(list 2240.389 869.4031) 
(list 2240.3784 869.4133) 
(list 2240.3687 869.4236) 
(list 2240.3602 869.4339) 
(list 2240.3533 869.4442) 
(list 2240.3481 869.4544) 
(list 2240.3448 869.4647) 
(list 2240.3435 869.475) 
(list 2240.3443 869.4853) 
(list 2240.3472 869.4956) 
(list 2240.3521 869.5058) 
(list 2240.3589 869.5161) 
(list 2240.3673 869.5264) 
(list 2240.3771 869.5367) 
(list 2240.3881 869.5469) 
(list 2240.4 869.5572) 
(list 2240.4122 869.5675) 
(list 2240.4246 869.5778) 
(list 2240.4367 869.5881) 
(list 2240.4481 869.5983) 
(list 2240.4585 869.6086) 
(list 2240.4676 869.6189) 
(list 2240.475 869.6292) 
(list 2240.4806 869.6394) 
(list 2240.4841 869.6497) 
(list 2240.4855 869.66) 
(list 2240.4855 869.66)))
(apply 'command (append '("pline") coords '("c")))
(setq tap7 (ssadd (entlast) tap7))
(command "_mirror" (entlast) "" "2240,900" "2240,901" "No")
(setq tap7 (ssadd (entlast) tap7))
(setq coords (list 
(list 2241.112 869.29) 
(list 2240.4855 869.29) 
(list 2240.4855 869.3003) 
(list 2240.4855 869.3106) 
(list 2240.4855 869.3208) 
(list 2240.4855 869.3311) 
(list 2240.4855 869.3414) 
(list 2240.4855 869.3517) 
(list 2240.4855 869.3619) 
(list 2240.4855 869.3722) 
(list 2240.4855 869.3825) 
(list 2240.4855 869.3928) 
(list 2240.4855 869.4031) 
(list 2240.4855 869.4133) 
(list 2240.4855 869.4236) 
(list 2240.4855 869.4339) 
(list 2240.4855 869.4442) 
(list 2240.4855 869.4544) 
(list 2240.4855 869.4647) 
(list 2240.4855 869.475) 
(list 2240.4855 869.4853) 
(list 2240.4855 869.4956) 
(list 2240.4855 869.5058) 
(list 2240.4855 869.5161) 
(list 2240.4855 869.5264) 
(list 2240.4855 869.5367) 
(list 2240.4855 869.5469) 
(list 2240.4855 869.5572) 
(list 2240.4855 869.5675) 
(list 2240.4855 869.5778) 
(list 2240.4855 869.5881) 
(list 2240.4855 869.5983) 
(list 2240.4855 869.6086) 
(list 2240.4855 869.6189) 
(list 2240.4855 869.6292) 
(list 2240.4855 869.6394) 
(list 2240.4855 869.6497) 
(list 2240.4855 869.66) 
(list 2241.112 869.66)))
(apply 'command (append '("pline") coords '("c")))
(setq tap7 (ssadd (entlast) tap7))
(command "_mirror" (entlast) "" "2240,900" "2240,901" "No")
(setq tap7 (ssadd (entlast) tap7))
(setq coords (list 
(list 2240 869.66) 
(list 2240.125 869.66) 
(list 2240.125 869.6703) 
(list 2240.125 869.6806) 
(list 2240.125 869.6908) 
(list 2240.125 869.7011) 
(list 2240.125 869.7114) 
(list 2240.125 869.7217) 
(list 2240.125 869.7319) 
(list 2240.125 869.7422) 
(list 2240.125 869.7525) 
(list 2240.125 869.7628) 
(list 2240.125 869.7731) 
(list 2240.125 869.7833) 
(list 2240.125 869.7936) 
(list 2240.125 869.8039) 
(list 2240.125 869.8142) 
(list 2240.125 869.8244) 
(list 2240.125 869.8347) 
(list 2240.125 869.845) 
(list 2240.125 869.8553) 
(list 2240.125 869.8656) 
(list 2240.125 869.8758) 
(list 2240.125 869.8861) 
(list 2240.125 869.8964) 
(list 2240.125 869.9067) 
(list 2240.125 869.9169) 
(list 2240.125 869.9272) 
(list 2240.125 869.9375) 
(list 2240.125 869.9478) 
(list 2240.125 869.9581) 
(list 2240.125 869.9683) 
(list 2240.125 869.9786) 
(list 2240.125 869.9889) 
(list 2240.125 869.9992) 
(list 2240.125 870.0094) 
(list 2240.125 870.0197) 
(list 2240.125 870.03) 
(list 2240 870.03)))
(apply 'command (append '("pline") coords '("c")))
(setq tap7 (ssadd (entlast) tap7))
(command "_mirror" (entlast) "" "2240,900" "2240,901" "No")
(setq tap7 (ssadd (entlast) tap7))
(setq coords (list 
(list 2240.4956 869.66) 
(list 2240.4855 869.66) 
(list 2240.4847 869.6703) 
(list 2240.4817 869.6806) 
(list 2240.4765 869.6908) 
(list 2240.4693 869.7011) 
(list 2240.4604 869.7114) 
(list 2240.4499 869.7217) 
(list 2240.4382 869.7319) 
(list 2240.4257 869.7422) 
(list 2240.4127 869.7525) 
(list 2240.3996 869.7628) 
(list 2240.3868 869.7731) 
(list 2240.3747 869.7833) 
(list 2240.3637 869.7936) 
(list 2240.3541 869.8039) 
(list 2240.3463 869.8142) 
(list 2240.3404 869.8244) 
(list 2240.3367 869.8347) 
(list 2240.3353 869.845) 
(list 2240.3363 869.8553) 
(list 2240.3396 869.8656) 
(list 2240.3451 869.8758) 
(list 2240.3528 869.8861) 
(list 2240.3623 869.8964) 
(list 2240.3735 869.9067) 
(list 2240.386 869.9169) 
(list 2240.3993 869.9272) 
(list 2240.4132 869.9375) 
(list 2240.4271 869.9478) 
(list 2240.4407 869.9581) 
(list 2240.4536 869.9683) 
(list 2240.4653 869.9786) 
(list 2240.4755 869.9889) 
(list 2240.4839 869.9992) 
(list 2240.4901 870.0094) 
(list 2240.4941 870.0197) 
(list 2240.4956 870.03) 
(list 2240.4956 870.03)))
(apply 'command (append '("pline") coords '("c")))
(setq tap7 (ssadd (entlast) tap7))
(command "_mirror" (entlast) "" "2240,900" "2240,901" "No")
(setq tap7 (ssadd (entlast) tap7))
(setq coords (list 
(list 2241.112 869.66) 
(list 2240.4956 869.66) 
(list 2240.4956 869.6703) 
(list 2240.4956 869.6806) 
(list 2240.4956 869.6908) 
(list 2240.4956 869.7011) 
(list 2240.4956 869.7114) 
(list 2240.4956 869.7217) 
(list 2240.4956 869.7319) 
(list 2240.4956 869.7422) 
(list 2240.4956 869.7525) 
(list 2240.4956 869.7628) 
(list 2240.4956 869.7731) 
(list 2240.4956 869.7833) 
(list 2240.4956 869.7936) 
(list 2240.4956 869.8039) 
(list 2240.4956 869.8142) 
(list 2240.4956 869.8244) 
(list 2240.4956 869.8347) 
(list 2240.4956 869.845) 
(list 2240.4956 869.8553) 
(list 2240.4956 869.8656) 
(list 2240.4956 869.8758) 
(list 2240.4956 869.8861) 
(list 2240.4956 869.8964) 
(list 2240.4956 869.9067) 
(list 2240.4956 869.9169) 
(list 2240.4956 869.9272) 
(list 2240.4956 869.9375) 
(list 2240.4956 869.9478) 
(list 2240.4956 869.9581) 
(list 2240.4956 869.9683) 
(list 2240.4956 869.9786) 
(list 2240.4956 869.9889) 
(list 2240.4956 869.9992) 
(list 2240.4956 870.0094) 
(list 2240.4956 870.0197) 
(list 2240.4956 870.03) 
(list 2241.112 870.03)))
(apply 'command (append '("pline") coords '("c")))
(setq tap7 (ssadd (entlast) tap7))
(command "_mirror" (entlast) "" "2240,900" "2240,901" "No")
(setq tap7 (ssadd (entlast) tap7))
(setq coords (list 
(list 2240 870.03) 
(list 2240.125 870.03) 
(list 2240.125 870.0403) 
(list 2240.125 870.0506) 
(list 2240.125 870.0608) 
(list 2240.125 870.0711) 
(list 2240.125 870.0814) 
(list 2240.125 870.0917) 
(list 2240.125 870.1019) 
(list 2240.125 870.1122) 
(list 2240.125 870.1225) 
(list 2240.125 870.1328) 
(list 2240.125 870.1431) 
(list 2240.125 870.1533) 
(list 2240.125 870.1636) 
(list 2240.125 870.1739) 
(list 2240.125 870.1842) 
(list 2240.125 870.1944) 
(list 2240.125 870.2047) 
(list 2240.125 870.215) 
(list 2240.125 870.2253) 
(list 2240.125 870.2356) 
(list 2240.125 870.2458) 
(list 2240.125 870.2561) 
(list 2240.125 870.2664) 
(list 2240.125 870.2767) 
(list 2240.125 870.2869) 
(list 2240.125 870.2972) 
(list 2240.125 870.3075) 
(list 2240.125 870.3178) 
(list 2240.125 870.3281) 
(list 2240.125 870.3383) 
(list 2240.125 870.3486) 
(list 2240.125 870.3589) 
(list 2240.125 870.3692) 
(list 2240.125 870.3794) 
(list 2240.125 870.3897) 
(list 2240.125 870.4) 
(list 2240 870.4)))
(apply 'command (append '("pline") coords '("c")))
(setq tap7 (ssadd (entlast) tap7))
(command "_mirror" (entlast) "" "2240,900" "2240,901" "No")
(setq tap7 (ssadd (entlast) tap7))
(setq coords (list 
(list 2240.5057 870.03) 
(list 2240.4956 870.03) 
(list 2240.4946 870.0403) 
(list 2240.4912 870.0506) 
(list 2240.4853 870.0608) 
(list 2240.4772 870.0711) 
(list 2240.4672 870.0814) 
(list 2240.4554 870.0917) 
(list 2240.4423 870.1019) 
(list 2240.4282 870.1122) 
(list 2240.4136 870.1225) 
(list 2240.3989 870.1328) 
(list 2240.3846 870.1431) 
(list 2240.3711 870.1533) 
(list 2240.3588 870.1636) 
(list 2240.3481 870.1739) 
(list 2240.3393 870.1842) 
(list 2240.3328 870.1944) 
(list 2240.3286 870.2047) 
(list 2240.3271 870.215) 
(list 2240.3282 870.2253) 
(list 2240.3319 870.2356) 
(list 2240.3381 870.2458) 
(list 2240.3467 870.2561) 
(list 2240.3574 870.2664) 
(list 2240.3699 870.2767) 
(list 2240.3838 870.2869) 
(list 2240.3987 870.2972) 
(list 2240.4141 870.3075) 
(list 2240.4296 870.3178) 
(list 2240.4448 870.3281) 
(list 2240.4591 870.3383) 
(list 2240.4721 870.3486) 
(list 2240.4834 870.3589) 
(list 2240.4927 870.3692) 
(list 2240.4996 870.3794) 
(list 2240.504 870.3897) 
(list 2240.5057 870.4) 
(list 2240.5057 870.4)))
(apply 'command (append '("pline") coords '("c")))
(setq tap7 (ssadd (entlast) tap7))
(command "_mirror" (entlast) "" "2240,900" "2240,901" "No")
(setq tap7 (ssadd (entlast) tap7))
(setq coords (list 
(list 2241.112 870.03) 
(list 2240.5057 870.03) 
(list 2240.5057 870.0403) 
(list 2240.5057 870.0506) 
(list 2240.5057 870.0608) 
(list 2240.5057 870.0711) 
(list 2240.5057 870.0814) 
(list 2240.5057 870.0917) 
(list 2240.5057 870.1019) 
(list 2240.5057 870.1122) 
(list 2240.5057 870.1225) 
(list 2240.5057 870.1328) 
(list 2240.5057 870.1431) 
(list 2240.5057 870.1533) 
(list 2240.5057 870.1636) 
(list 2240.5057 870.1739) 
(list 2240.5057 870.1842) 
(list 2240.5057 870.1944) 
(list 2240.5057 870.2047) 
(list 2240.5057 870.215) 
(list 2240.5057 870.2253) 
(list 2240.5057 870.2356) 
(list 2240.5057 870.2458) 
(list 2240.5057 870.2561) 
(list 2240.5057 870.2664) 
(list 2240.5057 870.2767) 
(list 2240.5057 870.2869) 
(list 2240.5057 870.2972) 
(list 2240.5057 870.3075) 
(list 2240.5057 870.3178) 
(list 2240.5057 870.3281) 
(list 2240.5057 870.3383) 
(list 2240.5057 870.3486) 
(list 2240.5057 870.3589) 
(list 2240.5057 870.3692) 
(list 2240.5057 870.3794) 
(list 2240.5057 870.3897) 
(list 2240.5057 870.4) 
(list 2241.112 870.4)))
(apply 'command (append '("pline") coords '("c")))
(setq tap7 (ssadd (entlast) tap7))
(command "_mirror" (entlast) "" "2240,900" "2240,901" "No")
(setq tap7 (ssadd (entlast) tap7))
(setq coords (list 
(list 2240 870.4) 
(list 2240.125 870.4) 
(list 2240.125 870.4103) 
(list 2240.125 870.4206) 
(list 2240.125 870.4308) 
(list 2240.125 870.4411) 
(list 2240.125 870.4514) 
(list 2240.125 870.4617) 
(list 2240.125 870.4719) 
(list 2240.125 870.4822) 
(list 2240.125 870.4925) 
(list 2240.125 870.5028) 
(list 2240.125 870.5131) 
(list 2240.125 870.5233) 
(list 2240.125 870.5336) 
(list 2240.125 870.5439) 
(list 2240.125 870.5542) 
(list 2240.125 870.5644) 
(list 2240.125 870.5747) 
(list 2240.125 870.585) 
(list 2240.125 870.5953) 
(list 2240.125 870.6056) 
(list 2240.125 870.6158) 
(list 2240.125 870.6261) 
(list 2240.125 870.6364) 
(list 2240.125 870.6467) 
(list 2240.125 870.6569) 
(list 2240.125 870.6672) 
(list 2240.125 870.6775) 
(list 2240.125 870.6878) 
(list 2240.125 870.6981) 
(list 2240.125 870.7083) 
(list 2240.125 870.7186) 
(list 2240.125 870.7289) 
(list 2240.125 870.7392) 
(list 2240.125 870.7494) 
(list 2240.125 870.7597) 
(list 2240.125 870.77) 
(list 2240 870.77)))
(apply 'command (append '("pline") coords '("c")))
(setq tap7 (ssadd (entlast) tap7))
(command "_mirror" (entlast) "" "2240,900" "2240,901" "No")
(setq tap7 (ssadd (entlast) tap7))
(setq coords (list 
(list 2240.5157 870.4) 
(list 2240.5057 870.4) 
(list 2240.5046 870.4103) 
(list 2240.5007 870.4206) 
(list 2240.4942 870.4308) 
(list 2240.4852 870.4411) 
(list 2240.474 870.4514) 
(list 2240.4609 870.4617) 
(list 2240.4464 870.4719) 
(list 2240.4308 870.4822) 
(list 2240.4146 870.4925) 
(list 2240.3983 870.5028) 
(list 2240.3824 870.5131) 
(list 2240.3675 870.5233) 
(list 2240.3538 870.5336) 
(list 2240.342 870.5439) 
(list 2240.3323 870.5542) 
(list 2240.3251 870.5644) 
(list 2240.3206 870.5747) 
(list 2240.3189 870.585) 
(list 2240.3201 870.5953) 
(list 2240.3243 870.6056) 
(list 2240.3312 870.6158) 
(list 2240.3407 870.6261) 
(list 2240.3525 870.6364) 
(list 2240.3662 870.6467) 
(list 2240.3816 870.6569) 
(list 2240.398 870.6672) 
(list 2240.415 870.6775) 
(list 2240.4322 870.6878) 
(list 2240.4488 870.6981) 
(list 2240.4646 870.7083) 
(list 2240.4789 870.7186) 
(list 2240.4913 870.7289) 
(list 2240.5015 870.7392) 
(list 2240.5091 870.7494) 
(list 2240.5139 870.7597) 
(list 2240.5157 870.77) 
(list 2240.5157 870.77)))
(apply 'command (append '("pline") coords '("c")))
(setq tap7 (ssadd (entlast) tap7))
(command "_mirror" (entlast) "" "2240,900" "2240,901" "No")
(setq tap7 (ssadd (entlast) tap7))
(setq coords (list 
(list 2241.112 870.4) 
(list 2240.5157 870.4) 
(list 2240.5157 870.4103) 
(list 2240.5157 870.4206) 
(list 2240.5157 870.4308) 
(list 2240.5157 870.4411) 
(list 2240.5157 870.4514) 
(list 2240.5157 870.4617) 
(list 2240.5157 870.4719) 
(list 2240.5157 870.4822) 
(list 2240.5157 870.4925) 
(list 2240.5157 870.5028) 
(list 2240.5157 870.5131) 
(list 2240.5157 870.5233) 
(list 2240.5157 870.5336) 
(list 2240.5157 870.5439) 
(list 2240.5157 870.5542) 
(list 2240.5157 870.5644) 
(list 2240.5157 870.5747) 
(list 2240.5157 870.585) 
(list 2240.5157 870.5953) 
(list 2240.5157 870.6056) 
(list 2240.5157 870.6158) 
(list 2240.5157 870.6261) 
(list 2240.5157 870.6364) 
(list 2240.5157 870.6467) 
(list 2240.5157 870.6569) 
(list 2240.5157 870.6672) 
(list 2240.5157 870.6775) 
(list 2240.5157 870.6878) 
(list 2240.5157 870.6981) 
(list 2240.5157 870.7083) 
(list 2240.5157 870.7186) 
(list 2240.5157 870.7289) 
(list 2240.5157 870.7392) 
(list 2240.5157 870.7494) 
(list 2240.5157 870.7597) 
(list 2240.5157 870.77) 
(list 2241.112 870.77)))
(apply 'command (append '("pline") coords '("c")))
(setq tap7 (ssadd (entlast) tap7))
(command "_mirror" (entlast) "" "2240,900" "2240,901" "No")
(setq tap7 (ssadd (entlast) tap7))
(setq coords (list 
(list 2240 870.77) 
(list 2240.125 870.77) 
(list 2240.125 870.7803) 
(list 2240.125 870.7906) 
(list 2240.125 870.8008) 
(list 2240.125 870.8111) 
(list 2240.125 870.8214) 
(list 2240.125 870.8317) 
(list 2240.125 870.8419) 
(list 2240.125 870.8522) 
(list 2240.125 870.8625) 
(list 2240.125 870.8728) 
(list 2240.125 870.8831) 
(list 2240.125 870.8933) 
(list 2240.125 870.9036) 
(list 2240.125 870.9139) 
(list 2240.125 870.9242) 
(list 2240.125 870.9344) 
(list 2240.125 870.9447) 
(list 2240.125 870.955) 
(list 2240.125 870.9653) 
(list 2240.125 870.9756) 
(list 2240.125 870.9858) 
(list 2240.125 870.9961) 
(list 2240.125 871.0064) 
(list 2240.125 871.0167) 
(list 2240.125 871.0269) 
(list 2240.125 871.0372) 
(list 2240.125 871.0475) 
(list 2240.125 871.0578) 
(list 2240.125 871.0681) 
(list 2240.125 871.0783) 
(list 2240.125 871.0886) 
(list 2240.125 871.0989) 
(list 2240.125 871.1092) 
(list 2240.125 871.1194) 
(list 2240.125 871.1297) 
(list 2240.125 871.14) 
(list 2240 871.14)))
(apply 'command (append '("pline") coords '("c")))
(setq tap7 (ssadd (entlast) tap7))
(command "_mirror" (entlast) "" "2240,900" "2240,901" "No")
(setq tap7 (ssadd (entlast) tap7))
(setq coords (list 
(list 2240.5258 870.77) 
(list 2240.5157 870.77) 
(list 2240.5145 870.7803) 
(list 2240.5102 870.7906) 
(list 2240.503 870.8008) 
(list 2240.4931 870.8111) 
(list 2240.4808 870.8214) 
(list 2240.4664 870.8317) 
(list 2240.4504 870.8419) 
(list 2240.4333 870.8522) 
(list 2240.4155 870.8625) 
(list 2240.3976 870.8728) 
(list 2240.3802 870.8831) 
(list 2240.3638 870.8933) 
(list 2240.3489 870.9036) 
(list 2240.3359 870.9139) 
(list 2240.3254 870.9242) 
(list 2240.3175 870.9344) 
(list 2240.3125 870.9447) 
(list 2240.3107 870.955) 
(list 2240.3121 870.9653) 
(list 2240.3166 870.9756) 
(list 2240.3242 870.9858) 
(list 2240.3346 870.9961) 
(list 2240.3475 871.0064) 
(list 2240.3626 871.0167) 
(list 2240.3794 871.0269) 
(list 2240.3973 871.0372) 
(list 2240.416 871.0475) 
(list 2240.4347 871.0578) 
(list 2240.4529 871.0681) 
(list 2240.4701 871.0783) 
(list 2240.4857 871.0886) 
(list 2240.4993 871.0989) 
(list 2240.5104 871.1092) 
(list 2240.5187 871.1194) 
(list 2240.5239 871.1297) 
(list 2240.5258 871.14) 
(list 2240.5258 871.14)))
(apply 'command (append '("pline") coords '("c")))
(setq tap7 (ssadd (entlast) tap7))
(command "_mirror" (entlast) "" "2240,900" "2240,901" "No")
(setq tap7 (ssadd (entlast) tap7))
(setq coords (list 
(list 2241.112 870.77) 
(list 2240.5258 870.77) 
(list 2240.5258 870.7803) 
(list 2240.5258 870.7906) 
(list 2240.5258 870.8008) 
(list 2240.5258 870.8111) 
(list 2240.5258 870.8214) 
(list 2240.5258 870.8317) 
(list 2240.5258 870.8419) 
(list 2240.5258 870.8522) 
(list 2240.5258 870.8625) 
(list 2240.5258 870.8728) 
(list 2240.5258 870.8831) 
(list 2240.5258 870.8933) 
(list 2240.5258 870.9036) 
(list 2240.5258 870.9139) 
(list 2240.5258 870.9242) 
(list 2240.5258 870.9344) 
(list 2240.5258 870.9447) 
(list 2240.5258 870.955) 
(list 2240.5258 870.9653) 
(list 2240.5258 870.9756) 
(list 2240.5258 870.9858) 
(list 2240.5258 870.9961) 
(list 2240.5258 871.0064) 
(list 2240.5258 871.0167) 
(list 2240.5258 871.0269) 
(list 2240.5258 871.0372) 
(list 2240.5258 871.0475) 
(list 2240.5258 871.0578) 
(list 2240.5258 871.0681) 
(list 2240.5258 871.0783) 
(list 2240.5258 871.0886) 
(list 2240.5258 871.0989) 
(list 2240.5258 871.1092) 
(list 2240.5258 871.1194) 
(list 2240.5258 871.1297) 
(list 2240.5258 871.14) 
(list 2241.112 871.14)))
(apply 'command (append '("pline") coords '("c")))
(setq tap7 (ssadd (entlast) tap7))
(command "_mirror" (entlast) "" "2240,900" "2240,901" "No")
(setq tap7 (ssadd (entlast) tap7))
(setq coords (list 
(list 2240 871.14) 
(list 2240.125 871.14) 
(list 2240.125 871.1503) 
(list 2240.125 871.1606) 
(list 2240.125 871.1708) 
(list 2240.125 871.1811) 
(list 2240.125 871.1914) 
(list 2240.125 871.2017) 
(list 2240.125 871.2119) 
(list 2240.125 871.2222) 
(list 2240.125 871.2325) 
(list 2240.125 871.2428) 
(list 2240.125 871.2531) 
(list 2240.125 871.2633) 
(list 2240.125 871.2736) 
(list 2240.125 871.2839) 
(list 2240.125 871.2942) 
(list 2240.125 871.3044) 
(list 2240.125 871.3147) 
(list 2240.125 871.325) 
(list 2240.125 871.3353) 
(list 2240.125 871.3456) 
(list 2240.125 871.3558) 
(list 2240.125 871.3661) 
(list 2240.125 871.3764) 
(list 2240.125 871.3867) 
(list 2240.125 871.3969) 
(list 2240.125 871.4072) 
(list 2240.125 871.4175) 
(list 2240.125 871.4278) 
(list 2240.125 871.4381) 
(list 2240.125 871.4483) 
(list 2240.125 871.4586) 
(list 2240.125 871.4689) 
(list 2240.125 871.4792) 
(list 2240.125 871.4894) 
(list 2240.125 871.4997) 
(list 2240.125 871.51) 
(list 2240 871.51)))
(apply 'command (append '("pline") coords '("c")))
(setq tap7 (ssadd (entlast) tap7))
(command "_mirror" (entlast) "" "2240,900" "2240,901" "No")
(setq tap7 (ssadd (entlast) tap7))
(setq coords (list 
(list 2240.5359 871.14) 
(list 2240.5258 871.14) 
(list 2240.5244 871.1503) 
(list 2240.5197 871.1606) 
(list 2240.5119 871.1708) 
(list 2240.501 871.1811) 
(list 2240.4876 871.1914) 
(list 2240.4719 871.2017) 
(list 2240.4545 871.2119) 
(list 2240.4358 871.2222) 
(list 2240.4164 871.2325) 
(list 2240.397 871.2428) 
(list 2240.378 871.2531) 
(list 2240.3602 871.2633) 
(list 2240.344 871.2736) 
(list 2240.3299 871.2839) 
(list 2240.3184 871.2942) 
(list 2240.3098 871.3044) 
(list 2240.3045 871.3147) 
(list 2240.3025 871.325) 
(list 2240.304 871.3353) 
(list 2240.309 871.3456) 
(list 2240.3172 871.3558) 
(list 2240.3285 871.3661) 
(list 2240.3426 871.3764) 
(list 2240.359 871.3867) 
(list 2240.3772 871.3969) 
(list 2240.3967 871.4072) 
(list 2240.4169 871.4175) 
(list 2240.4372 871.4278) 
(list 2240.457 871.4381) 
(list 2240.4756 871.4483) 
(list 2240.4925 871.4586) 
(list 2240.5072 871.4689) 
(list 2240.5192 871.4792) 
(list 2240.5282 871.4894) 
(list 2240.5338 871.4997) 
(list 2240.5359 871.51) 
(list 2240.5359 871.51)))
(apply 'command (append '("pline") coords '("c")))
(setq tap7 (ssadd (entlast) tap7))
(command "_mirror" (entlast) "" "2240,900" "2240,901" "No")
(setq tap7 (ssadd (entlast) tap7))
(setq coords (list 
(list 2241.112 871.14) 
(list 2240.5359 871.14) 
(list 2240.5359 871.1503) 
(list 2240.5359 871.1606) 
(list 2240.5359 871.1708) 
(list 2240.5359 871.1811) 
(list 2240.5359 871.1914) 
(list 2240.5359 871.2017) 
(list 2240.5359 871.2119) 
(list 2240.5359 871.2222) 
(list 2240.5359 871.2325) 
(list 2240.5359 871.2428) 
(list 2240.5359 871.2531) 
(list 2240.5359 871.2633) 
(list 2240.5359 871.2736) 
(list 2240.5359 871.2839) 
(list 2240.5359 871.2942) 
(list 2240.5359 871.3044) 
(list 2240.5359 871.3147) 
(list 2240.5359 871.325) 
(list 2240.5359 871.3353) 
(list 2240.5359 871.3456) 
(list 2240.5359 871.3558) 
(list 2240.5359 871.3661) 
(list 2240.5359 871.3764) 
(list 2240.5359 871.3867) 
(list 2240.5359 871.3969) 
(list 2240.5359 871.4072) 
(list 2240.5359 871.4175) 
(list 2240.5359 871.4278) 
(list 2240.5359 871.4381) 
(list 2240.5359 871.4483) 
(list 2240.5359 871.4586) 
(list 2240.5359 871.4689) 
(list 2240.5359 871.4792) 
(list 2240.5359 871.4894) 
(list 2240.5359 871.4997) 
(list 2240.5359 871.51) 
(list 2241.112 871.51)))
(apply 'command (append '("pline") coords '("c")))
(setq tap7 (ssadd (entlast) tap7))
(command "_mirror" (entlast) "" "2240,900" "2240,901" "No")
(setq tap7 (ssadd (entlast) tap7))
(setq coords (list 
(list 2240 871.51) 
(list 2240.125 871.51) 
(list 2240.125 871.5203) 
(list 2240.125 871.5306) 
(list 2240.125 871.5408) 
(list 2240.125 871.5511) 
(list 2240.125 871.5614) 
(list 2240.125 871.5717) 
(list 2240.125 871.5819) 
(list 2240.125 871.5922) 
(list 2240.125 871.6025) 
(list 2240.125 871.6128) 
(list 2240.125 871.6231) 
(list 2240.125 871.6333) 
(list 2240.125 871.6436) 
(list 2240.125 871.6539) 
(list 2240.125 871.6642) 
(list 2240.125 871.6744) 
(list 2240.125 871.6847) 
(list 2240.125 871.695) 
(list 2240.125 871.7053) 
(list 2240.125 871.7156) 
(list 2240.125 871.7258) 
(list 2240.125 871.7361) 
(list 2240.125 871.7464) 
(list 2240.125 871.7567) 
(list 2240.125 871.7669) 
(list 2240.125 871.7772) 
(list 2240.125 871.7875) 
(list 2240.125 871.7978) 
(list 2240.125 871.8081) 
(list 2240.125 871.8183) 
(list 2240.125 871.8286) 
(list 2240.125 871.8389) 
(list 2240.125 871.8492) 
(list 2240.125 871.8594) 
(list 2240.125 871.8697) 
(list 2240.125 871.88) 
(list 2240 871.88)))
(apply 'command (append '("pline") coords '("c")))
(setq tap7 (ssadd (entlast) tap7))
(command "_mirror" (entlast) "" "2240,900" "2240,901" "No")
(setq tap7 (ssadd (entlast) tap7))
(setq coords (list 
(list 2240.5459 871.51) 
(list 2240.5359 871.51) 
(list 2240.5343 871.5203) 
(list 2240.5292 871.5306) 
(list 2240.5207 871.5408) 
(list 2240.509 871.5511) 
(list 2240.4944 871.5614) 
(list 2240.4774 871.5717) 
(list 2240.4585 871.5819) 
(list 2240.4383 871.5922) 
(list 2240.4174 871.6025) 
(list 2240.3963 871.6128) 
(list 2240.3759 871.6231) 
(list 2240.3566 871.6333) 
(list 2240.339 871.6436) 
(list 2240.3238 871.6539) 
(list 2240.3114 871.6642) 
(list 2240.3022 871.6744) 
(list 2240.2964 871.6847) 
(list 2240.2943 871.695) 
(list 2240.296 871.7053) 
(list 2240.3013 871.7156) 
(list 2240.3102 871.7258) 
(list 2240.3225 871.7361) 
(list 2240.3377 871.7464) 
(list 2240.3553 871.7567) 
(list 2240.375 871.7669) 
(list 2240.396 871.7772) 
(list 2240.4178 871.7875) 
(list 2240.4397 871.7978) 
(list 2240.461 871.8081) 
(list 2240.4811 871.8183) 
(list 2240.4993 871.8286) 
(list 2240.5151 871.8389) 
(list 2240.5281 871.8492) 
(list 2240.5377 871.8594) 
(list 2240.5437 871.8697) 
(list 2240.5459 871.88) 
(list 2240.5459 871.88)))
(apply 'command (append '("pline") coords '("c")))
(setq tap7 (ssadd (entlast) tap7))
(command "_mirror" (entlast) "" "2240,900" "2240,901" "No")
(setq tap7 (ssadd (entlast) tap7))
(setq coords (list 
(list 2241.112 871.51) 
(list 2240.5459 871.51) 
(list 2240.5459 871.5203) 
(list 2240.5459 871.5306) 
(list 2240.5459 871.5408) 
(list 2240.5459 871.5511) 
(list 2240.5459 871.5614) 
(list 2240.5459 871.5717) 
(list 2240.5459 871.5819) 
(list 2240.5459 871.5922) 
(list 2240.5459 871.6025) 
(list 2240.5459 871.6128) 
(list 2240.5459 871.6231) 
(list 2240.5459 871.6333) 
(list 2240.5459 871.6436) 
(list 2240.5459 871.6539) 
(list 2240.5459 871.6642) 
(list 2240.5459 871.6744) 
(list 2240.5459 871.6847) 
(list 2240.5459 871.695) 
(list 2240.5459 871.7053) 
(list 2240.5459 871.7156) 
(list 2240.5459 871.7258) 
(list 2240.5459 871.7361) 
(list 2240.5459 871.7464) 
(list 2240.5459 871.7567) 
(list 2240.5459 871.7669) 
(list 2240.5459 871.7772) 
(list 2240.5459 871.7875) 
(list 2240.5459 871.7978) 
(list 2240.5459 871.8081) 
(list 2240.5459 871.8183) 
(list 2240.5459 871.8286) 
(list 2240.5459 871.8389) 
(list 2240.5459 871.8492) 
(list 2240.5459 871.8594) 
(list 2240.5459 871.8697) 
(list 2240.5459 871.88) 
(list 2241.112 871.88)))
(apply 'command (append '("pline") coords '("c")))
(setq tap7 (ssadd (entlast) tap7))
(command "_mirror" (entlast) "" "2240,900" "2240,901" "No")
(setq tap7 (ssadd (entlast) tap7))
(setq coords (list 
(list 2240 871.88) 
(list 2240.125 871.88) 
(list 2240.125 871.8903) 
(list 2240.125 871.9006) 
(list 2240.125 871.9108) 
(list 2240.125 871.9211) 
(list 2240.125 871.9314) 
(list 2240.125 871.9417) 
(list 2240.125 871.9519) 
(list 2240.125 871.9622) 
(list 2240.125 871.9725) 
(list 2240.125 871.9828) 
(list 2240.125 871.9931) 
(list 2240.125 872.0033) 
(list 2240.125 872.0136) 
(list 2240.125 872.0239) 
(list 2240.125 872.0342) 
(list 2240.125 872.0444) 
(list 2240.125 872.0547) 
(list 2240.125 872.065) 
(list 2240.125 872.0753) 
(list 2240.125 872.0856) 
(list 2240.125 872.0958) 
(list 2240.125 872.1061) 
(list 2240.125 872.1164) 
(list 2240.125 872.1267) 
(list 2240.125 872.1369) 
(list 2240.125 872.1472) 
(list 2240.125 872.1575) 
(list 2240.125 872.1678) 
(list 2240.125 872.1781) 
(list 2240.125 872.1883) 
(list 2240.125 872.1986) 
(list 2240.125 872.2089) 
(list 2240.125 872.2192) 
(list 2240.125 872.2294) 
(list 2240.125 872.2397) 
(list 2240.125 872.25) 
(list 2240 872.25)))
(apply 'command (append '("pline") coords '("c")))
(setq tap7 (ssadd (entlast) tap7))
(command "_mirror" (entlast) "" "2240,900" "2240,901" "No")
(setq tap7 (ssadd (entlast) tap7))
(setq coords (list 
(list 2240.556 871.88) 
(list 2240.5459 871.88) 
(list 2240.5443 871.8903) 
(list 2240.5388 871.9006) 
(list 2240.5295 871.9108) 
(list 2240.5169 871.9211) 
(list 2240.5012 871.9314) 
(list 2240.4829 871.9417) 
(list 2240.4626 871.9519) 
(list 2240.4408 871.9622) 
(list 2240.4183 871.9725) 
(list 2240.3957 871.9828) 
(list 2240.3737 871.9931) 
(list 2240.3529 872.0033) 
(list 2240.3341 872.0136) 
(list 2240.3178 872.0239) 
(list 2240.3044 872.0342) 
(list 2240.2945 872.0444) 
(list 2240.2883 872.0547) 
(list 2240.2861 872.065) 
(list 2240.2879 872.0753) 
(list 2240.2937 872.0856) 
(list 2240.3033 872.0958) 
(list 2240.3164 872.1061) 
(list 2240.3327 872.1164) 
(list 2240.3517 872.1267) 
(list 2240.3728 872.1369) 
(list 2240.3954 872.1472) 
(list 2240.4188 872.1575) 
(list 2240.4422 872.1678) 
(list 2240.4651 872.1781) 
(list 2240.4866 872.1883) 
(list 2240.5061 872.1986) 
(list 2240.5231 872.2089) 
(list 2240.5369 872.2192) 
(list 2240.5472 872.2294) 
(list 2240.5536 872.2397) 
(list 2240.556 872.25) 
(list 2240.556 872.25)))
(apply 'command (append '("pline") coords '("c")))
(setq tap7 (ssadd (entlast) tap7))
(command "_mirror" (entlast) "" "2240,900" "2240,901" "No")
(setq tap7 (ssadd (entlast) tap7))
(setq coords (list 
(list 2241.112 871.88) 
(list 2240.556 871.88) 
(list 2240.556 871.8903) 
(list 2240.556 871.9006) 
(list 2240.556 871.9108) 
(list 2240.556 871.9211) 
(list 2240.556 871.9314) 
(list 2240.556 871.9417) 
(list 2240.556 871.9519) 
(list 2240.556 871.9622) 
(list 2240.556 871.9725) 
(list 2240.556 871.9828) 
(list 2240.556 871.9931) 
(list 2240.556 872.0033) 
(list 2240.556 872.0136) 
(list 2240.556 872.0239) 
(list 2240.556 872.0342) 
(list 2240.556 872.0444) 
(list 2240.556 872.0547) 
(list 2240.556 872.065) 
(list 2240.556 872.0753) 
(list 2240.556 872.0856) 
(list 2240.556 872.0958) 
(list 2240.556 872.1061) 
(list 2240.556 872.1164) 
(list 2240.556 872.1267) 
(list 2240.556 872.1369) 
(list 2240.556 872.1472) 
(list 2240.556 872.1575) 
(list 2240.556 872.1678) 
(list 2240.556 872.1781) 
(list 2240.556 872.1883) 
(list 2240.556 872.1986) 
(list 2240.556 872.2089) 
(list 2240.556 872.2192) 
(list 2240.556 872.2294) 
(list 2240.556 872.2397) 
(list 2240.556 872.25) 
(list 2241.112 872.25)))
(apply 'command (append '("pline") coords '("c")))
(setq tap7 (ssadd (entlast) tap7))
(command "_mirror" (entlast) "" "2240,900" "2240,901" "No")
(setq tap7 (ssadd (entlast) tap7))
(command "_block" "blktap7" "2240,900" tap7 "")
(command "_insert" "blktap7" "2240,900" "1" "1" "0")
(command "_insert" "blktap7" "2240,900" "1" "1" "180")
(setq uc7 nil)
(setq uc7 (ssadd))
(setq coords (list 
(list 0 -0.185) 
(list 0.125 -0.185) 
(list 0.125 -0.17472) 
(list 0.125 -0.16444) 
(list 0.125 -0.15417) 
(list 0.125 -0.14389) 
(list 0.125 -0.13361) 
(list 0.125 -0.12333) 
(list 0.125 -0.11306) 
(list 0.125 -0.10278) 
(list 0.125 -0.0925) 
(list 0.125 -0.082222) 
(list 0.125 -0.071944) 
(list 0.125 -0.061667) 
(list 0.125 -0.051389) 
(list 0.125 -0.041111) 
(list 0.125 -0.030833) 
(list 0.125 -0.020556) 
(list 0.125 -0.010278) 
(list 0.125 0) 
(list 0.125 0.010278) 
(list 0.125 0.020556) 
(list 0.125 0.030833) 
(list 0.125 0.041111) 
(list 0.125 0.051389) 
(list 0.125 0.061667) 
(list 0.125 0.071944) 
(list 0.125 0.082222) 
(list 0.125 0.0925) 
(list 0.125 0.10278) 
(list 0.125 0.11306) 
(list 0.125 0.12333) 
(list 0.125 0.13361) 
(list 0.125 0.14389) 
(list 0.125 0.15417) 
(list 0.125 0.16444) 
(list 0.125 0.17472) 
(list 0.125 0.185) 
(list 0 0.185)))
(apply 'command (append '("pline") coords '("c")))
(setq uc7 (ssadd (entlast) uc7))
(setq coords (list 
(list 1.112 -0.185) 
(list 0.556 -0.185) 
(list 0.55392 -0.17472) 
(list 0.54774 -0.16444) 
(list 0.53765 -0.15417) 
(list 0.52395 -0.14389) 
(list 0.50706 -0.13361) 
(list 0.4875 -0.12333) 
(list 0.46586 -0.11306) 
(list 0.44279 -0.10278) 
(list 0.419 -0.0925) 
(list 0.39521 -0.082222) 
(list 0.37214 -0.071944) 
(list 0.3505 -0.061667) 
(list 0.33094 -0.051389) 
(list 0.31405 -0.041111) 
(list 0.30035 -0.030833) 
(list 0.29026 -0.020556) 
(list 0.28408 -0.010278) 
(list 0.282 0) 
(list 0.28408 0.010278) 
(list 0.29026 0.020556) 
(list 0.30035 0.030833) 
(list 0.31405 0.041111) 
(list 0.33094 0.051389) 
(list 0.3505 0.061667) 
(list 0.37214 0.071944) 
(list 0.39521 0.082222) 
(list 0.419 0.0925) 
(list 0.44279 0.10278) 
(list 0.46586 0.11306) 
(list 0.4875 0.12333) 
(list 0.50706 0.13361) 
(list 0.52395 0.14389) 
(list 0.53765 0.15417) 
(list 0.54774 0.16444) 
(list 0.55392 0.17472) 
(list 0.556 0.185) 
(list 1.112 0.185)))
(apply 'command (append '("pline") coords '("c")))
(setq uc7 (ssadd (entlast) uc7))
(command "_block" "blkuc7" "0,0.185" uc7 "")
(command "_insert" "blkuc7" "2240,872.62" "1" "1" "0")
(command "_insert" "blkuc7" "2240,872.25" "1" "1" "180")
(command "_insert" "blkuc7" "2240,872.99" "1" "1" "0")
(command "_insert" "blkuc7" "2240,872.62" "1" "1" "180")
(command "_insert" "blkuc7" "2240,873.36" "1" "1" "0")
(command "_insert" "blkuc7" "2240,872.99" "1" "1" "180")
(command "_insert" "blkuc7" "2240,873.73" "1" "1" "0")
(command "_insert" "blkuc7" "2240,873.36" "1" "1" "180")
(command "_insert" "blkuc7" "2240,874.1" "1" "1" "0")
(command "_insert" "blkuc7" "2240,873.73" "1" "1" "180")
(command "_insert" "blkuc7" "2240,874.47" "1" "1" "0")
(command "_insert" "blkuc7" "2240,874.1" "1" "1" "180")
(command "_insert" "blkuc7" "2240,874.84" "1" "1" "0")
(command "_insert" "blkuc7" "2240,874.47" "1" "1" "180")
(command "_insert" "blkuc7" "2240,875.21" "1" "1" "0")
(command "_insert" "blkuc7" "2240,874.84" "1" "1" "180")
(command "_insert" "blkuc7" "2240,875.58" "1" "1" "0")
(command "_insert" "blkuc7" "2240,875.21" "1" "1" "180")
(command "_insert" "blkuc7" "2240,875.95" "1" "1" "0")
(command "_insert" "blkuc7" "2240,875.58" "1" "1" "180")
(command "_insert" "blkuc7" "2240,876.32" "1" "1" "0")
(command "_insert" "blkuc7" "2240,875.95" "1" "1" "180")
(command "_insert" "blkuc7" "2240,876.69" "1" "1" "0")
(command "_insert" "blkuc7" "2240,876.32" "1" "1" "180")
(command "_insert" "blkuc7" "2240,877.06" "1" "1" "0")
(command "_insert" "blkuc7" "2240,876.69" "1" "1" "180")
(command "_insert" "blkuc7" "2240,877.43" "1" "1" "0")
(command "_insert" "blkuc7" "2240,877.06" "1" "1" "180")
(command "_insert" "blkuc7" "2240,877.8" "1" "1" "0")
(command "_insert" "blkuc7" "2240,877.43" "1" "1" "180")
(command "_insert" "blkuc7" "2240,878.17" "1" "1" "0")
(command "_insert" "blkuc7" "2240,877.8" "1" "1" "180")
(command "_insert" "blkuc7" "2240,878.54" "1" "1" "0")
(command "_insert" "blkuc7" "2240,878.17" "1" "1" "180")
(command "_insert" "blkuc7" "2240,878.91" "1" "1" "0")
(command "_insert" "blkuc7" "2240,878.54" "1" "1" "180")
(command "_insert" "blkuc7" "2240,879.28" "1" "1" "0")
(command "_insert" "blkuc7" "2240,878.91" "1" "1" "180")
(command "_insert" "blkuc7" "2240,879.65" "1" "1" "0")
(command "_insert" "blkuc7" "2240,879.28" "1" "1" "180")
(command "_insert" "blkuc7" "2240,880.02" "1" "1" "0")
(command "_insert" "blkuc7" "2240,879.65" "1" "1" "180")
(command "_insert" "blkuc7" "2240,880.39" "1" "1" "0")
(command "_insert" "blkuc7" "2240,880.02" "1" "1" "180")
(command "_insert" "blkuc7" "2240,880.76" "1" "1" "0")
(command "_insert" "blkuc7" "2240,880.39" "1" "1" "180")
(command "_insert" "blkuc7" "2240,881.13" "1" "1" "0")
(command "_insert" "blkuc7" "2240,880.76" "1" "1" "180")
(command "_insert" "blkuc7" "2240,881.5" "1" "1" "0")
(command "_insert" "blkuc7" "2240,881.13" "1" "1" "180")
(command "_insert" "blkuc7" "2240,881.87" "1" "1" "0")
(command "_insert" "blkuc7" "2240,881.5" "1" "1" "180")
(command "_insert" "blkuc7" "2240,882.24" "1" "1" "0")
(command "_insert" "blkuc7" "2240,881.87" "1" "1" "180")
(command "_insert" "blkuc7" "2240,882.61" "1" "1" "0")
(command "_insert" "blkuc7" "2240,882.24" "1" "1" "180")
(command "_insert" "blkuc7" "2240,882.98" "1" "1" "0")
(command "_insert" "blkuc7" "2240,882.61" "1" "1" "180")
(command "_insert" "blkuc7" "2240,883.35" "1" "1" "0")
(command "_insert" "blkuc7" "2240,882.98" "1" "1" "180")
(command "_insert" "blkuc7" "2240,883.72" "1" "1" "0")
(command "_insert" "blkuc7" "2240,883.35" "1" "1" "180")
(command "_insert" "blkuc7" "2240,884.09" "1" "1" "0")
(command "_insert" "blkuc7" "2240,883.72" "1" "1" "180")
(command "_insert" "blkuc7" "2240,884.46" "1" "1" "0")
(command "_insert" "blkuc7" "2240,884.09" "1" "1" "180")
(command "_insert" "blkuc7" "2240,884.83" "1" "1" "0")
(command "_insert" "blkuc7" "2240,884.46" "1" "1" "180")
(command "_insert" "blkuc7" "2240,885.2" "1" "1" "0")
(command "_insert" "blkuc7" "2240,884.83" "1" "1" "180")
(command "_insert" "blkuc7" "2240,885.57" "1" "1" "0")
(command "_insert" "blkuc7" "2240,885.2" "1" "1" "180")
(command "_insert" "blkuc7" "2240,885.94" "1" "1" "0")
(command "_insert" "blkuc7" "2240,885.57" "1" "1" "180")
(command "_insert" "blkuc7" "2240,886.31" "1" "1" "0")
(command "_insert" "blkuc7" "2240,885.94" "1" "1" "180")
(command "_insert" "blkuc7" "2240,886.68" "1" "1" "0")
(command "_insert" "blkuc7" "2240,886.31" "1" "1" "180")
(command "_insert" "blkuc7" "2240,887.05" "1" "1" "0")
(command "_insert" "blkuc7" "2240,886.68" "1" "1" "180")
(command "_insert" "blkuc7" "2240,887.42" "1" "1" "0")
(command "_insert" "blkuc7" "2240,887.05" "1" "1" "180")
(command "_insert" "blkuc7" "2240,887.79" "1" "1" "0")
(command "_insert" "blkuc7" "2240,887.42" "1" "1" "180")
(command "_insert" "blkuc7" "2240,888.16" "1" "1" "0")
(command "_insert" "blkuc7" "2240,887.79" "1" "1" "180")
(command "_insert" "blkuc7" "2240,888.53" "1" "1" "0")
(command "_insert" "blkuc7" "2240,888.16" "1" "1" "180")
(command "_insert" "blkuc7" "2240,888.9" "1" "1" "0")
(command "_insert" "blkuc7" "2240,888.53" "1" "1" "180")
(command "_insert" "blkuc7" "2240,889.27" "1" "1" "0")
(command "_insert" "blkuc7" "2240,888.9" "1" "1" "180")
(command "_insert" "blkuc7" "2240,889.64" "1" "1" "0")
(command "_insert" "blkuc7" "2240,889.27" "1" "1" "180")
(command "_insert" "blkuc7" "2240,890.01" "1" "1" "0")
(command "_insert" "blkuc7" "2240,889.64" "1" "1" "180")
(command "_insert" "blkuc7" "2240,890.38" "1" "1" "0")
(command "_insert" "blkuc7" "2240,890.01" "1" "1" "180")
(command "_insert" "blkuc7" "2240,890.75" "1" "1" "0")
(command "_insert" "blkuc7" "2240,890.38" "1" "1" "180")
(command "_insert" "blkuc7" "2240,891.12" "1" "1" "0")
(command "_insert" "blkuc7" "2240,890.75" "1" "1" "180")
(command "_insert" "blkuc7" "2240,891.49" "1" "1" "0")
(command "_insert" "blkuc7" "2240,891.12" "1" "1" "180")
(command "_insert" "blkuc7" "2240,891.86" "1" "1" "0")
(command "_insert" "blkuc7" "2240,891.49" "1" "1" "180")
(command "_insert" "blkuc7" "2240,892.23" "1" "1" "0")
(command "_insert" "blkuc7" "2240,891.86" "1" "1" "180")
(command "_insert" "blkuc7" "2240,892.6" "1" "1" "0")
(command "_insert" "blkuc7" "2240,892.23" "1" "1" "180")
(command "_insert" "blkuc7" "2240,892.97" "1" "1" "0")
(command "_insert" "blkuc7" "2240,892.6" "1" "1" "180")
(command "_insert" "blkuc7" "2240,893.34" "1" "1" "0")
(command "_insert" "blkuc7" "2240,892.97" "1" "1" "180")
(command "_insert" "blkuc7" "2240,893.71" "1" "1" "0")
(command "_insert" "blkuc7" "2240,893.34" "1" "1" "180")
(command "_insert" "blkuc7" "2240,894.08" "1" "1" "0")
(command "_insert" "blkuc7" "2240,893.71" "1" "1" "180")
(command "_insert" "blkuc7" "2240,894.45" "1" "1" "0")
(command "_insert" "blkuc7" "2240,894.08" "1" "1" "180")
(command "_insert" "blkuc7" "2240,894.82" "1" "1" "0")
(command "_insert" "blkuc7" "2240,894.45" "1" "1" "180")
(command "_insert" "blkuc7" "2240,895.19" "1" "1" "0")
(command "_insert" "blkuc7" "2240,894.82" "1" "1" "180")
(command "_insert" "blkuc7" "2240,895.56" "1" "1" "0")
(command "_insert" "blkuc7" "2240,895.19" "1" "1" "180")
(command "_insert" "blkuc7" "2240,895.93" "1" "1" "0")
(command "_insert" "blkuc7" "2240,895.56" "1" "1" "180")
(command "_insert" "blkuc7" "2240,896.3" "1" "1" "0")
(command "_insert" "blkuc7" "2240,895.93" "1" "1" "180")
(command "_insert" "blkuc7" "2240,896.67" "1" "1" "0")
(command "_insert" "blkuc7" "2240,896.3" "1" "1" "180")
(command "_insert" "blkuc7" "2240,897.04" "1" "1" "0")
(command "_insert" "blkuc7" "2240,896.67" "1" "1" "180")
(command "_insert" "blkuc7" "2240,897.41" "1" "1" "0")
(command "_insert" "blkuc7" "2240,897.04" "1" "1" "180")
(command "_insert" "blkuc7" "2240,897.78" "1" "1" "0")
(command "_insert" "blkuc7" "2240,897.41" "1" "1" "180")
(command "_insert" "blkuc7" "2240,898.15" "1" "1" "0")
(command "_insert" "blkuc7" "2240,897.78" "1" "1" "180")
(command "_insert" "blkuc7" "2240,898.52" "1" "1" "0")
(command "_insert" "blkuc7" "2240,898.15" "1" "1" "180")
(command "_insert" "blkuc7" "2240,898.89" "1" "1" "0")
(command "_insert" "blkuc7" "2240,898.52" "1" "1" "180")
(command "_insert" "blkuc7" "2240,899.26" "1" "1" "0")
(command "_insert" "blkuc7" "2240,898.89" "1" "1" "180")
(command "_insert" "blkuc7" "2240,899.63" "1" "1" "0")
(command "_insert" "blkuc7" "2240,899.26" "1" "1" "180")
(command "_insert" "blkuc7" "2240,900" "1" "1" "0")
(command "_insert" "blkuc7" "2240,899.63" "1" "1" "180")
(command "_insert" "blkuc7" "2240,900.37" "1" "1" "0")
(command "_insert" "blkuc7" "2240,900" "1" "1" "180")
(command "_insert" "blkuc7" "2240,900.74" "1" "1" "0")
(command "_insert" "blkuc7" "2240,900.37" "1" "1" "180")
(command "_insert" "blkuc7" "2240,901.11" "1" "1" "0")
(command "_insert" "blkuc7" "2240,900.74" "1" "1" "180")
(command "_insert" "blkuc7" "2240,901.48" "1" "1" "0")
(command "_insert" "blkuc7" "2240,901.11" "1" "1" "180")
(command "_insert" "blkuc7" "2240,901.85" "1" "1" "0")
(command "_insert" "blkuc7" "2240,901.48" "1" "1" "180")
(command "_insert" "blkuc7" "2240,902.22" "1" "1" "0")
(command "_insert" "blkuc7" "2240,901.85" "1" "1" "180")
(command "_insert" "blkuc7" "2240,902.59" "1" "1" "0")
(command "_insert" "blkuc7" "2240,902.22" "1" "1" "180")
(command "_insert" "blkuc7" "2240,902.96" "1" "1" "0")
(command "_insert" "blkuc7" "2240,902.59" "1" "1" "180")
(command "_insert" "blkuc7" "2240,903.33" "1" "1" "0")
(command "_insert" "blkuc7" "2240,902.96" "1" "1" "180")
(command "_insert" "blkuc7" "2240,903.7" "1" "1" "0")
(command "_insert" "blkuc7" "2240,903.33" "1" "1" "180")
(command "_insert" "blkuc7" "2240,904.07" "1" "1" "0")
(command "_insert" "blkuc7" "2240,903.7" "1" "1" "180")
(command "_insert" "blkuc7" "2240,904.44" "1" "1" "0")
(command "_insert" "blkuc7" "2240,904.07" "1" "1" "180")
(command "_insert" "blkuc7" "2240,904.81" "1" "1" "0")
(command "_insert" "blkuc7" "2240,904.44" "1" "1" "180")
(command "_insert" "blkuc7" "2240,905.18" "1" "1" "0")
(command "_insert" "blkuc7" "2240,904.81" "1" "1" "180")
(command "_insert" "blkuc7" "2240,905.55" "1" "1" "0")
(command "_insert" "blkuc7" "2240,905.18" "1" "1" "180")
(command "_insert" "blkuc7" "2240,905.92" "1" "1" "0")
(command "_insert" "blkuc7" "2240,905.55" "1" "1" "180")
(command "_insert" "blkuc7" "2240,906.29" "1" "1" "0")
(command "_insert" "blkuc7" "2240,905.92" "1" "1" "180")
(command "_insert" "blkuc7" "2240,906.66" "1" "1" "0")
(command "_insert" "blkuc7" "2240,906.29" "1" "1" "180")
(command "_insert" "blkuc7" "2240,907.03" "1" "1" "0")
(command "_insert" "blkuc7" "2240,906.66" "1" "1" "180")
(command "_insert" "blkuc7" "2240,907.4" "1" "1" "0")
(command "_insert" "blkuc7" "2240,907.03" "1" "1" "180")
(command "_insert" "blkuc7" "2240,907.77" "1" "1" "0")
(command "_insert" "blkuc7" "2240,907.4" "1" "1" "180")
(command "_insert" "blkuc7" "2240,908.14" "1" "1" "0")
(command "_insert" "blkuc7" "2240,907.77" "1" "1" "180")
(command "_insert" "blkuc7" "2240,908.51" "1" "1" "0")
(command "_insert" "blkuc7" "2240,908.14" "1" "1" "180")
(command "_insert" "blkuc7" "2240,908.88" "1" "1" "0")
(command "_insert" "blkuc7" "2240,908.51" "1" "1" "180")
(command "_insert" "blkuc7" "2240,909.25" "1" "1" "0")
(command "_insert" "blkuc7" "2240,908.88" "1" "1" "180")
(command "_insert" "blkuc7" "2240,909.62" "1" "1" "0")
(command "_insert" "blkuc7" "2240,909.25" "1" "1" "180")
(command "_insert" "blkuc7" "2240,909.99" "1" "1" "0")
(command "_insert" "blkuc7" "2240,909.62" "1" "1" "180")
(command "_insert" "blkuc7" "2240,910.36" "1" "1" "0")
(command "_insert" "blkuc7" "2240,909.99" "1" "1" "180")
(command "_insert" "blkuc7" "2240,910.73" "1" "1" "0")
(command "_insert" "blkuc7" "2240,910.36" "1" "1" "180")
(command "_insert" "blkuc7" "2240,911.1" "1" "1" "0")
(command "_insert" "blkuc7" "2240,910.73" "1" "1" "180")
(command "_insert" "blkuc7" "2240,911.47" "1" "1" "0")
(command "_insert" "blkuc7" "2240,911.1" "1" "1" "180")
(command "_insert" "blkuc7" "2240,911.84" "1" "1" "0")
(command "_insert" "blkuc7" "2240,911.47" "1" "1" "180")
(command "_insert" "blkuc7" "2240,912.21" "1" "1" "0")
(command "_insert" "blkuc7" "2240,911.84" "1" "1" "180")
(command "_insert" "blkuc7" "2240,912.58" "1" "1" "0")
(command "_insert" "blkuc7" "2240,912.21" "1" "1" "180")
(command "_insert" "blkuc7" "2240,912.95" "1" "1" "0")
(command "_insert" "blkuc7" "2240,912.58" "1" "1" "180")
(command "_insert" "blkuc7" "2240,913.32" "1" "1" "0")
(command "_insert" "blkuc7" "2240,912.95" "1" "1" "180")
(command "_insert" "blkuc7" "2240,913.69" "1" "1" "0")
(command "_insert" "blkuc7" "2240,913.32" "1" "1" "180")
(command "_insert" "blkuc7" "2240,914.06" "1" "1" "0")
(command "_insert" "blkuc7" "2240,913.69" "1" "1" "180")
(command "_insert" "blkuc7" "2240,914.43" "1" "1" "0")
(command "_insert" "blkuc7" "2240,914.06" "1" "1" "180")
(command "_insert" "blkuc7" "2240,914.8" "1" "1" "0")
(command "_insert" "blkuc7" "2240,914.43" "1" "1" "180")
(command "_insert" "blkuc7" "2240,915.17" "1" "1" "0")
(command "_insert" "blkuc7" "2240,914.8" "1" "1" "180")
(command "_insert" "blkuc7" "2240,915.54" "1" "1" "0")
(command "_insert" "blkuc7" "2240,915.17" "1" "1" "180")
(command "_insert" "blkuc7" "2240,915.91" "1" "1" "0")
(command "_insert" "blkuc7" "2240,915.54" "1" "1" "180")
(command "_insert" "blkuc7" "2240,916.28" "1" "1" "0")
(command "_insert" "blkuc7" "2240,915.91" "1" "1" "180")
(command "_insert" "blkuc7" "2240,916.65" "1" "1" "0")
(command "_insert" "blkuc7" "2240,916.28" "1" "1" "180")
(command "_insert" "blkuc7" "2240,917.02" "1" "1" "0")
(command "_insert" "blkuc7" "2240,916.65" "1" "1" "180")
(command "_insert" "blkuc7" "2240,917.39" "1" "1" "0")
(command "_insert" "blkuc7" "2240,917.02" "1" "1" "180")
(command "_insert" "blkuc7" "2240,917.76" "1" "1" "0")
(command "_insert" "blkuc7" "2240,917.39" "1" "1" "180")
(command "_insert" "blkuc7" "2240,918.13" "1" "1" "0")
(command "_insert" "blkuc7" "2240,917.76" "1" "1" "180")
(command "_insert" "blkuc7" "2240,918.5" "1" "1" "0")
(command "_insert" "blkuc7" "2240,918.13" "1" "1" "180")
(command "_insert" "blkuc7" "2240,918.87" "1" "1" "0")
(command "_insert" "blkuc7" "2240,918.5" "1" "1" "180")
(command "_insert" "blkuc7" "2240,919.24" "1" "1" "0")
(command "_insert" "blkuc7" "2240,918.87" "1" "1" "180")
(command "_insert" "blkuc7" "2240,919.61" "1" "1" "0")
(command "_insert" "blkuc7" "2240,919.24" "1" "1" "180")
(command "_insert" "blkuc7" "2240,919.98" "1" "1" "0")
(command "_insert" "blkuc7" "2240,919.61" "1" "1" "180")
(command "_insert" "blkuc7" "2240,920.35" "1" "1" "0")
(command "_insert" "blkuc7" "2240,919.98" "1" "1" "180")
(command "_insert" "blkuc7" "2240,920.72" "1" "1" "0")
(command "_insert" "blkuc7" "2240,920.35" "1" "1" "180")
(command "_insert" "blkuc7" "2240,921.09" "1" "1" "0")
(command "_insert" "blkuc7" "2240,920.72" "1" "1" "180")
(command "_insert" "blkuc7" "2240,921.46" "1" "1" "0")
(command "_insert" "blkuc7" "2240,921.09" "1" "1" "180")
(command "_insert" "blkuc7" "2240,921.83" "1" "1" "0")
(command "_insert" "blkuc7" "2240,921.46" "1" "1" "180")
(command "_insert" "blkuc7" "2240,922.2" "1" "1" "0")
(command "_insert" "blkuc7" "2240,921.83" "1" "1" "180")
(command "_insert" "blkuc7" "2240,922.57" "1" "1" "0")
(command "_insert" "blkuc7" "2240,922.2" "1" "1" "180")
(command "_insert" "blkuc7" "2240,922.94" "1" "1" "0")
(command "_insert" "blkuc7" "2240,922.57" "1" "1" "180")
(command "_insert" "blkuc7" "2240,923.31" "1" "1" "0")
(command "_insert" "blkuc7" "2240,922.94" "1" "1" "180")
(command "_insert" "blkuc7" "2240,923.68" "1" "1" "0")
(command "_insert" "blkuc7" "2240,923.31" "1" "1" "180")
(command "_insert" "blkuc7" "2240,924.05" "1" "1" "0")
(command "_insert" "blkuc7" "2240,923.68" "1" "1" "180")
(command "_insert" "blkuc7" "2240,924.42" "1" "1" "0")
(command "_insert" "blkuc7" "2240,924.05" "1" "1" "180")
(command "_insert" "blkuc7" "2240,924.79" "1" "1" "0")
(command "_insert" "blkuc7" "2240,924.42" "1" "1" "180")
(command "_insert" "blkuc7" "2240,925.16" "1" "1" "0")
(command "_insert" "blkuc7" "2240,924.79" "1" "1" "180")
(command "_insert" "blkuc7" "2240,925.53" "1" "1" "0")
(command "_insert" "blkuc7" "2240,925.16" "1" "1" "180")
(command "_insert" "blkuc7" "2240,925.9" "1" "1" "0")
(command "_insert" "blkuc7" "2240,925.53" "1" "1" "180")
(command "_insert" "blkuc7" "2240,926.27" "1" "1" "0")
(command "_insert" "blkuc7" "2240,925.9" "1" "1" "180")
(command "_insert" "blkuc7" "2240,926.64" "1" "1" "0")
(command "_insert" "blkuc7" "2240,926.27" "1" "1" "180")
(command "_insert" "blkuc7" "2240,927.01" "1" "1" "0")
(command "_insert" "blkuc7" "2240,926.64" "1" "1" "180")
(command "_insert" "blkuc7" "2240,927.38" "1" "1" "0")
(command "_insert" "blkuc7" "2240,927.01" "1" "1" "180")
(command "_insert" "blkuc7" "2240,927.75" "1" "1" "0")
(command "_insert" "blkuc7" "2240,927.38" "1" "1" "180")
(command "_layer" "set" "phccover" "")
(command "_rectangle" "2238.888,933.3" "2241.112,866.7")
(command "_layer" "set" "nitride" "")
(setq phc7 currobj)
(command "_layer" "set" "cover" "")
(command "_rectangle" "2238.888,836.7" "2241.112,963.3")
(command "_layer" "set" "nitride" "")
(command "_layer" "set" "text" "")
(command "_circle" "2237.938,846.7" "0.075")
(command "_circle" "2237.563,846.7" "0.15")
(command "_circle" "2237.188,846.7" "0.075")
(command "_circle" "2236.813,846.7" "0.15")
(command "_circle" "2237.938,848.7" "0.075")
(command "_circle" "2237.563,848.7" "0.075")
(command "_circle" "2237.188,848.7" "0.15")
(command "_circle" "2236.813,848.7" "0.15")
(command "_circle" "2237.938,850.7" "0.075")
(command "_circle" "2237.563,850.7" "0.15")
(command "_circle" "2237.188,850.7" "0.15")
(command "_circle" "2236.813,850.7" "0.15")
(command "_circle" "2237.938,852.7" "0.075")
(command "_circle" "2237.563,852.7" "0.075")
(command "_circle" "2237.188,852.7" "0.075")
(command "_circle" "2236.813,852.7" "0.075")
(command "_circle" "2236.438,852.7" "0.15")
(command "_circle" "2237.938,854.7" "0.075")
(command "_circle" "2237.563,854.7" "0.15")
(command "_circle" "2237.188,854.7" "0.075")
(command "_circle" "2236.813,854.7" "0.075")
(command "_circle" "2236.438,854.7" "0.15")
(command "_circle" "2237.938,856.7" "0.075")
(command "_circle" "2237.563,856.7" "0.075")
(command "_circle" "2237.188,856.7" "0.15")
(command "_circle" "2236.813,856.7" "0.075")
(command "_circle" "2236.438,856.7" "0.15")
(command "_circle" "2237.938,858.7" "0.075")
(command "_circle" "2237.563,858.7" "0.15")
(command "_circle" "2237.188,858.7" "0.15")
(command "_circle" "2236.813,858.7" "0.075")
(command "_circle" "2236.438,858.7" "0.15")
(command "_circle" "2237.938,860.7" "0.075")
(command "_circle" "2237.563,860.7" "0.075")
(command "_circle" "2237.188,860.7" "0.075")
(command "_circle" "2236.813,860.7" "0.15")
(command "_circle" "2236.438,860.7" "0.15")
(command "_circle" "2237.938,862.7" "0.075")
(command "_circle" "2237.563,862.7" "0.15")
(command "_circle" "2237.188,862.7" "0.075")
(command "_circle" "2236.813,862.7" "0.15")
(command "_circle" "2236.438,862.7" "0.15")
(command "_circle" "2237.938,864.7" "0.075")
(command "_circle" "2237.563,864.7" "0.075")
(command "_circle" "2237.188,864.7" "0.15")
(command "_circle" "2236.813,864.7" "0.15")
(command "_circle" "2236.438,864.7" "0.15")
(command "_circle" "2237.938,866.7" "0.075")
(command "_circle" "2237.563,866.7" "0.15")
(command "_circle" "2237.188,866.7" "0.15")
(command "_circle" "2236.813,866.7" "0.15")
(command "_circle" "2236.438,866.7" "0.15")
(command "_circle" "2237.938,868.7" "0.075")
(command "_circle" "2237.563,868.7" "0.075")
(command "_circle" "2237.188,868.7" "0.075")
(command "_circle" "2236.813,868.7" "0.075")
(command "_circle" "2236.438,868.7" "0.075")
(command "_circle" "2236.063,868.7" "0.15")
(command "_circle" "2237.938,870.7" "0.075")
(command "_circle" "2237.563,870.7" "0.15")
(command "_circle" "2237.188,870.7" "0.075")
(command "_circle" "2236.813,870.7" "0.075")
(command "_circle" "2236.438,870.7" "0.075")
(command "_circle" "2236.063,870.7" "0.15")
(command "_circle" "2237.938,872.7" "0.075")
(command "_circle" "2237.563,872.7" "0.075")
(command "_circle" "2237.188,872.7" "0.15")
(command "_circle" "2236.813,872.7" "0.075")
(command "_circle" "2236.438,872.7" "0.075")
(command "_circle" "2236.063,872.7" "0.15")
(command "_circle" "2237.938,874.7" "0.075")
(command "_circle" "2237.563,874.7" "0.15")
(command "_circle" "2237.188,874.7" "0.15")
(command "_circle" "2236.813,874.7" "0.075")
(command "_circle" "2236.438,874.7" "0.075")
(command "_circle" "2236.063,874.7" "0.15")
(command "_circle" "2237.938,876.7" "0.075")
(command "_circle" "2237.563,876.7" "0.075")
(command "_circle" "2237.188,876.7" "0.075")
(command "_circle" "2236.813,876.7" "0.15")
(command "_circle" "2236.438,876.7" "0.075")
(command "_circle" "2236.063,876.7" "0.15")
(command "_circle" "2237.938,878.7" "0.075")
(command "_circle" "2237.563,878.7" "0.15")
(command "_circle" "2237.188,878.7" "0.075")
(command "_circle" "2236.813,878.7" "0.15")
(command "_circle" "2236.438,878.7" "0.075")
(command "_circle" "2236.063,878.7" "0.15")
(command "_circle" "2237.938,880.7" "0.075")
(command "_circle" "2237.563,880.7" "0.075")
(command "_circle" "2237.188,880.7" "0.15")
(command "_circle" "2236.813,880.7" "0.15")
(command "_circle" "2236.438,880.7" "0.075")
(command "_circle" "2236.063,880.7" "0.15")
(command "_circle" "2237.938,882.7" "0.075")
(command "_circle" "2237.563,882.7" "0.15")
(command "_circle" "2237.188,882.7" "0.15")
(command "_circle" "2236.813,882.7" "0.15")
(command "_circle" "2236.438,882.7" "0.075")
(command "_circle" "2236.063,882.7" "0.15")
(command "_circle" "2237.938,884.7" "0.075")
(command "_circle" "2237.563,884.7" "0.075")
(command "_circle" "2237.188,884.7" "0.075")
(command "_circle" "2236.813,884.7" "0.075")
(command "_circle" "2236.438,884.7" "0.15")
(command "_circle" "2236.063,884.7" "0.15")
(command "_circle" "2237.938,886.7" "0.075")
(command "_circle" "2237.563,886.7" "0.15")
(command "_circle" "2237.188,886.7" "0.075")
(command "_circle" "2236.813,886.7" "0.075")
(command "_circle" "2236.438,886.7" "0.15")
(command "_circle" "2236.063,886.7" "0.15")
(command "_circle" "2237.938,888.7" "0.075")
(command "_circle" "2237.563,888.7" "0.075")
(command "_circle" "2237.188,888.7" "0.15")
(command "_circle" "2236.813,888.7" "0.075")
(command "_circle" "2236.438,888.7" "0.15")
(command "_circle" "2236.063,888.7" "0.15")
(command "_circle" "2237.938,890.7" "0.075")
(command "_circle" "2237.563,890.7" "0.15")
(command "_circle" "2237.188,890.7" "0.15")
(command "_circle" "2236.813,890.7" "0.075")
(command "_circle" "2236.438,890.7" "0.15")
(command "_circle" "2236.063,890.7" "0.15")
(command "_circle" "2237.938,892.7" "0.075")
(command "_circle" "2237.563,892.7" "0.075")
(command "_circle" "2237.188,892.7" "0.075")
(command "_circle" "2236.813,892.7" "0.15")
(command "_circle" "2236.438,892.7" "0.15")
(command "_circle" "2236.063,892.7" "0.15")
(command "_circle" "2237.938,894.7" "0.075")
(command "_circle" "2237.563,894.7" "0.15")
(command "_circle" "2237.188,894.7" "0.075")
(command "_circle" "2236.813,894.7" "0.15")
(command "_circle" "2236.438,894.7" "0.15")
(command "_circle" "2236.063,894.7" "0.15")
(command "_circle" "2237.938,896.7" "0.075")
(command "_circle" "2237.563,896.7" "0.075")
(command "_circle" "2237.188,896.7" "0.15")
(command "_circle" "2236.813,896.7" "0.15")
(command "_circle" "2236.438,896.7" "0.15")
(command "_circle" "2236.063,896.7" "0.15")
(command "_circle" "2237.938,898.7" "0.075")
(command "_circle" "2237.563,898.7" "0.15")
(command "_circle" "2237.188,898.7" "0.15")
(command "_circle" "2236.813,898.7" "0.15")
(command "_circle" "2236.438,898.7" "0.15")
(command "_circle" "2236.063,898.7" "0.15")
(command "_circle" "2237.938,900.7" "0.075")
(command "_circle" "2237.563,900.7" "0.075")
(command "_circle" "2237.188,900.7" "0.075")
(command "_circle" "2236.813,900.7" "0.075")
(command "_circle" "2236.438,900.7" "0.075")
(command "_circle" "2236.063,900.7" "0.075")
(command "_circle" "2235.688,900.7" "0.15")
(command "_circle" "2237.938,902.7" "0.075")
(command "_circle" "2237.563,902.7" "0.15")
(command "_circle" "2237.188,902.7" "0.075")
(command "_circle" "2236.813,902.7" "0.075")
(command "_circle" "2236.438,902.7" "0.075")
(command "_circle" "2236.063,902.7" "0.075")
(command "_circle" "2235.688,902.7" "0.15")
(command "_circle" "2237.938,904.7" "0.075")
(command "_circle" "2237.563,904.7" "0.075")
(command "_circle" "2237.188,904.7" "0.15")
(command "_circle" "2236.813,904.7" "0.075")
(command "_circle" "2236.438,904.7" "0.075")
(command "_circle" "2236.063,904.7" "0.075")
(command "_circle" "2235.688,904.7" "0.15")
(command "_circle" "2237.938,906.7" "0.075")
(command "_circle" "2237.563,906.7" "0.15")
(command "_circle" "2237.188,906.7" "0.15")
(command "_circle" "2236.813,906.7" "0.075")
(command "_circle" "2236.438,906.7" "0.075")
(command "_circle" "2236.063,906.7" "0.075")
(command "_circle" "2235.688,906.7" "0.15")
(command "_circle" "2237.938,908.7" "0.075")
(command "_circle" "2237.563,908.7" "0.075")
(command "_circle" "2237.188,908.7" "0.075")
(command "_circle" "2236.813,908.7" "0.15")
(command "_circle" "2236.438,908.7" "0.075")
(command "_circle" "2236.063,908.7" "0.075")
(command "_circle" "2235.688,908.7" "0.15")
(command "_circle" "2237.938,910.7" "0.075")
(command "_circle" "2237.563,910.7" "0.15")
(command "_circle" "2237.188,910.7" "0.075")
(command "_circle" "2236.813,910.7" "0.15")
(command "_circle" "2236.438,910.7" "0.075")
(command "_circle" "2236.063,910.7" "0.075")
(command "_circle" "2235.688,910.7" "0.15")
(command "_circle" "2237.938,912.7" "0.075")
(command "_circle" "2237.563,912.7" "0.075")
(command "_circle" "2237.188,912.7" "0.15")
(command "_circle" "2236.813,912.7" "0.15")
(command "_circle" "2236.438,912.7" "0.075")
(command "_circle" "2236.063,912.7" "0.075")
(command "_circle" "2235.688,912.7" "0.15")
(command "_circle" "2237.938,914.7" "0.075")
(command "_circle" "2237.563,914.7" "0.15")
(command "_circle" "2237.188,914.7" "0.15")
(command "_circle" "2236.813,914.7" "0.15")
(command "_circle" "2236.438,914.7" "0.075")
(command "_circle" "2236.063,914.7" "0.075")
(command "_circle" "2235.688,914.7" "0.15")
(command "_circle" "2237.938,916.7" "0.075")
(command "_circle" "2237.563,916.7" "0.075")
(command "_circle" "2237.188,916.7" "0.075")
(command "_circle" "2236.813,916.7" "0.075")
(command "_circle" "2236.438,916.7" "0.15")
(command "_circle" "2236.063,916.7" "0.075")
(command "_circle" "2235.688,916.7" "0.15")
(command "_circle" "2237.938,918.7" "0.075")
(command "_circle" "2237.563,918.7" "0.15")
(command "_circle" "2237.188,918.7" "0.075")
(command "_circle" "2236.813,918.7" "0.075")
(command "_circle" "2236.438,918.7" "0.15")
(command "_circle" "2236.063,918.7" "0.075")
(command "_circle" "2235.688,918.7" "0.15")
(command "_circle" "2237.938,920.7" "0.075")
(command "_circle" "2237.563,920.7" "0.075")
(command "_circle" "2237.188,920.7" "0.15")
(command "_circle" "2236.813,920.7" "0.075")
(command "_circle" "2236.438,920.7" "0.15")
(command "_circle" "2236.063,920.7" "0.075")
(command "_circle" "2235.688,920.7" "0.15")
(command "_circle" "2237.938,922.7" "0.075")
(command "_circle" "2237.563,922.7" "0.15")
(command "_circle" "2237.188,922.7" "0.15")
(command "_circle" "2236.813,922.7" "0.075")
(command "_circle" "2236.438,922.7" "0.15")
(command "_circle" "2236.063,922.7" "0.075")
(command "_circle" "2235.688,922.7" "0.15")
(command "_circle" "2237.938,924.7" "0.075")
(command "_circle" "2237.563,924.7" "0.075")
(command "_circle" "2237.188,924.7" "0.075")
(command "_circle" "2236.813,924.7" "0.15")
(command "_circle" "2236.438,924.7" "0.15")
(command "_circle" "2236.063,924.7" "0.075")
(command "_circle" "2235.688,924.7" "0.15")
(command "_circle" "2237.938,926.7" "0.075")
(command "_circle" "2237.563,926.7" "0.15")
(command "_circle" "2237.188,926.7" "0.075")
(command "_circle" "2236.813,926.7" "0.15")
(command "_circle" "2236.438,926.7" "0.15")
(command "_circle" "2236.063,926.7" "0.075")
(command "_circle" "2235.688,926.7" "0.15")
(command "_circle" "2237.938,928.7" "0.075")
(command "_circle" "2237.563,928.7" "0.075")
(command "_circle" "2237.188,928.7" "0.15")
(command "_circle" "2236.813,928.7" "0.15")
(command "_circle" "2236.438,928.7" "0.15")
(command "_circle" "2236.063,928.7" "0.075")
(command "_circle" "2235.688,928.7" "0.15")
(command "_circle" "2237.938,930.7" "0.075")
(command "_circle" "2237.563,930.7" "0.15")
(command "_circle" "2237.188,930.7" "0.15")
(command "_circle" "2236.813,930.7" "0.15")
(command "_circle" "2236.438,930.7" "0.15")
(command "_circle" "2236.063,930.7" "0.075")
(command "_circle" "2235.688,930.7" "0.15")
(command "_circle" "2237.938,932.7" "0.075")
(command "_circle" "2237.563,932.7" "0.075")
(command "_circle" "2237.188,932.7" "0.075")
(command "_circle" "2236.813,932.7" "0.075")
(command "_circle" "2236.438,932.7" "0.075")
(command "_circle" "2236.063,932.7" "0.15")
(command "_circle" "2235.688,932.7" "0.15")
(command "_circle" "2237.938,934.7" "0.075")
(command "_circle" "2237.563,934.7" "0.15")
(command "_circle" "2237.188,934.7" "0.075")
(command "_circle" "2236.813,934.7" "0.075")
(command "_circle" "2236.438,934.7" "0.075")
(command "_circle" "2236.063,934.7" "0.15")
(command "_circle" "2235.688,934.7" "0.15")
(command "_circle" "2237.938,936.7" "0.075")
(command "_circle" "2237.563,936.7" "0.075")
(command "_circle" "2237.188,936.7" "0.15")
(command "_circle" "2236.813,936.7" "0.075")
(command "_circle" "2236.438,936.7" "0.075")
(command "_circle" "2236.063,936.7" "0.15")
(command "_circle" "2235.688,936.7" "0.15")
(command "_circle" "2237.938,938.7" "0.075")
(command "_circle" "2237.563,938.7" "0.15")
(command "_circle" "2237.188,938.7" "0.15")
(command "_circle" "2236.813,938.7" "0.075")
(command "_circle" "2236.438,938.7" "0.075")
(command "_circle" "2236.063,938.7" "0.15")
(command "_circle" "2235.688,938.7" "0.15")
(command "_circle" "2237.938,940.7" "0.075")
(command "_circle" "2237.563,940.7" "0.075")
(command "_circle" "2237.188,940.7" "0.075")
(command "_circle" "2236.813,940.7" "0.15")
(command "_circle" "2236.438,940.7" "0.075")
(command "_circle" "2236.063,940.7" "0.15")
(command "_circle" "2235.688,940.7" "0.15")
(command "_circle" "2237.938,942.7" "0.075")
(command "_circle" "2237.563,942.7" "0.15")
(command "_circle" "2237.188,942.7" "0.075")
(command "_circle" "2236.813,942.7" "0.15")
(command "_circle" "2236.438,942.7" "0.075")
(command "_circle" "2236.063,942.7" "0.15")
(command "_circle" "2235.688,942.7" "0.15")
(command "_circle" "2237.938,944.7" "0.075")
(command "_circle" "2237.563,944.7" "0.075")
(command "_circle" "2237.188,944.7" "0.15")
(command "_circle" "2236.813,944.7" "0.15")
(command "_circle" "2236.438,944.7" "0.075")
(command "_circle" "2236.063,944.7" "0.15")
(command "_circle" "2235.688,944.7" "0.15")
(command "_circle" "2237.938,946.7" "0.075")
(command "_circle" "2237.563,946.7" "0.15")
(command "_circle" "2237.188,946.7" "0.15")
(command "_circle" "2236.813,946.7" "0.15")
(command "_circle" "2236.438,946.7" "0.075")
(command "_circle" "2236.063,946.7" "0.15")
(command "_circle" "2235.688,946.7" "0.15")
(command "_circle" "2237.938,948.7" "0.075")
(command "_circle" "2237.563,948.7" "0.075")
(command "_circle" "2237.188,948.7" "0.075")
(command "_circle" "2236.813,948.7" "0.075")
(command "_circle" "2236.438,948.7" "0.15")
(command "_circle" "2236.063,948.7" "0.15")
(command "_circle" "2235.688,948.7" "0.15")
(command "_circle" "2237.938,950.7" "0.075")
(command "_circle" "2237.563,950.7" "0.15")
(command "_circle" "2237.188,950.7" "0.075")
(command "_circle" "2236.813,950.7" "0.075")
(command "_circle" "2236.438,950.7" "0.15")
(command "_circle" "2236.063,950.7" "0.15")
(command "_circle" "2235.688,950.7" "0.15")
(command "_circle" "2237.938,952.7" "0.075")
(command "_circle" "2237.563,952.7" "0.075")
(command "_circle" "2237.188,952.7" "0.15")
(command "_circle" "2236.813,952.7" "0.075")
(command "_circle" "2236.438,952.7" "0.15")
(command "_circle" "2236.063,952.7" "0.15")
(command "_circle" "2235.688,952.7" "0.15")
(command "_circle" "2237.938,954.7" "0.075")
(command "_circle" "2237.563,954.7" "0.15")
(command "_circle" "2237.188,954.7" "0.15")
(command "_circle" "2236.813,954.7" "0.075")
(command "_circle" "2236.438,954.7" "0.15")
(command "_circle" "2236.063,954.7" "0.15")
(command "_circle" "2235.688,954.7" "0.15")
(command "_circle" "2237.938,956.7" "0.075")
(command "_circle" "2237.563,956.7" "0.075")
(command "_circle" "2237.188,956.7" "0.075")
(command "_circle" "2236.813,956.7" "0.15")
(command "_circle" "2236.438,956.7" "0.15")
(command "_circle" "2236.063,956.7" "0.15")
(command "_circle" "2235.688,956.7" "0.15")
(command "_circle" "2237.938,958.7" "0.075")
(command "_circle" "2237.563,958.7" "0.15")
(command "_circle" "2237.188,958.7" "0.075")
(command "_circle" "2236.813,958.7" "0.15")
(command "_circle" "2236.438,958.7" "0.15")
(command "_circle" "2236.063,958.7" "0.15")
(command "_circle" "2235.688,958.7" "0.15")
(command "_circle" "2237.938,960.7" "0.075")
(command "_circle" "2237.563,960.7" "0.075")
(command "_circle" "2237.188,960.7" "0.15")
(command "_circle" "2236.813,960.7" "0.15")
(command "_circle" "2236.438,960.7" "0.15")
(command "_circle" "2236.063,960.7" "0.15")
(command "_circle" "2235.688,960.7" "0.15")
(command "_circle" "2237.938,962.7" "0.075")
(command "_circle" "2237.563,962.7" "0.15")
(command "_circle" "2237.188,962.7" "0.15")
(command "_circle" "2236.813,962.7" "0.15")
(command "_circle" "2236.438,962.7" "0.15")
(command "_circle" "2236.063,962.7" "0.15")
(command "_circle" "2235.688,962.7" "0.15")
(command "_layer" "set" "nitride" "")
(command "_layer" "set" "text" "")
(command-s "_text" "2226.888,963.3" "2" "-90" "a = 370 nm" )
(sssetfirst nil (ssget "_L"))
(if (not (numberp (vl-string-search "Mac" (getvar "platform")))) (c:txtexp))
(command "_layer" "set" "nitride" "")
(command "_layer" "set" "text" "")
(command-s "_text" "2223.888,963.3" "2" "-90" "gap = 250 nm" )
(sssetfirst nil (ssget "_L"))
(if (not (numberp (vl-string-search "Mac" (getvar "platform")))) (c:txtexp))
(command "_layer" "set" "nitride" "")
(command "_layer" "set" "text" "")
(command-s "_text" "2220.888,963.3" "2" "-90" "amplitude = 137 nm" )
(sssetfirst nil (ssget "_L"))
(if (not (numberp (vl-string-search "Mac" (getvar "platform")))) (c:txtexp))
(command "_layer" "set" "nitride" "")
(command "_layer" "set" "text" "")
(command-s "_text" "2217.888,963.3" "2" "-90" "start width = 280 nm" )
(sssetfirst nil (ssget "_L"))
(if (not (numberp (vl-string-search "Mac" (getvar "platform")))) (c:txtexp))
(command "_layer" "set" "nitride" "")
(command "_layer" "set" "text" "")
(command-s "_text" "2214.888,963.3" "2" "-90" "width = 294 nm" )
(sssetfirst nil (ssget "_L"))
(if (not (numberp (vl-string-search "Mac" (getvar "platform")))) (c:txtexp))
(command "_layer" "set" "nitride" "")
(command "_layer" "set" "text" "")
(command-s "_text" "2211.888,963.3" "2" "-90" "taper: 15" )
(sssetfirst nil (ssget "_L"))
(if (not (numberp (vl-string-search "Mac" (getvar "platform")))) (c:txtexp))
(command "_layer" "set" "nitride" "")
(command "_layer" "set" "text" "")
(command-s "_text" "2208.888,963.3" "2" "-90" "nominal: 150" )
(sssetfirst nil (ssget "_L"))
(if (not (numberp (vl-string-search "Mac" (getvar "platform")))) (c:txtexp))
(command "_layer" "set" "nitride" "")
(command "_layer" "set" "indicators" "")
(setq coords (list 
(list 2160.415 940) 
(list 2160.415 920) 
(list 2140.415 900) 
(list 2160.415 880) 
(list 2160.415 860) 
(list 2160.415 900) 
(list 2160.415 887.0711) 
(list 2147.4861 900) 
(list 2160.415 912.9289) 
(list 2160.415 900)))
(apply 'command (append '("pline") coords '("c")))
(command "._fillet" "radius" "1" "._fillet" "P" (entlast))
(setq coords (list 
(list 2319.585 940) 
(list 2319.585 920) 
(list 2339.585 900) 
(list 2319.585 880) 
(list 2319.585 860) 
(list 2319.585 900) 
(list 2319.585 887.0711) 
(list 2332.5139 900) 
(list 2319.585 912.9289) 
(list 2319.585 900)))
(apply 'command (append '("pline") coords '("c")))
(command "._fillet" "radius" "1" "._fillet" "P" (entlast))
(command "_layer" "set" "holes" "")
(command "_circle" "2158.0629,914.1124" "0.5")
(command "_circle" "2155.7109,911.7603" "0.5")
(command "_circle" "2153.3588,909.4083" "0.5")
(command "_circle" "2151.0067,907.0562" "0.5")
(command "_circle" "2148.6547,904.7041" "0.5")
(command "_circle" "2146.3026,902.3521" "0.5")
(command "_circle" "2143.9505,900" "0.5")
(command "_circle" "2146.3026,897.6479" "0.5")
(command "_circle" "2148.6547,895.2959" "0.5")
(command "_circle" "2151.0067,892.9438" "0.5")
(command "_circle" "2153.3588,890.5917" "0.5")
(command "_circle" "2155.7109,888.2397" "0.5")
(command "_circle" "2158.0629,885.8876" "0.5")
(command "_circle" "2321.9371,914.1124" "0.5")
(command "_circle" "2324.2891,911.7603" "0.5")
(command "_circle" "2326.6412,909.4083" "0.5")
(command "_circle" "2328.9933,907.0562" "0.5")
(command "_circle" "2331.3453,904.7041" "0.5")
(command "_circle" "2333.6974,902.3521" "0.5")
(command "_circle" "2336.0495,900" "0.5")
(command "_circle" "2333.6974,897.6479" "0.5")
(command "_circle" "2331.3453,895.2959" "0.5")
(command "_circle" "2328.9933,892.9438" "0.5")
(command "_circle" "2326.6412,890.5917" "0.5")
(command "_circle" "2324.2891,888.2397" "0.5")
(command "_circle" "2321.9371,885.8876" "0.5")
(command "_layer" "set" "nitride" "")
(command "_block" "blkcoupler7" "2240,900" coupler7 "")
(command "_insert" "blkcoupler7" "2240,900" "1" "1" "0")
(command "_insert" "blkcoupler7" "2240,900" "1" "1" "180")
(command "_block" "blksinglenanobeam7" "2240,900" singlenanobeam7 "")
(command "_insert" "blksinglenanobeam7" "2240,900" "1" "1" "0")
(command "_insert" "blksinglenanobeam7" "2240,900" "1" "1" "180")
(command "_block" "blkanglednodearray7" "2240,900" anglednodearray7 "")
(command "_insert" "blkanglednodearray7" "2240,900" "1" "1" "0")
(command "_insert" "blkanglednodearray7" "2240,900" "1" "1" "180")
(command "_block" "blkcooledsinglenanobeam7" "2240,900" cooledsinglenanobeam7 "")
(command "_insert" "blkcooledsinglenanobeam7" "2240,900" "1" "1" "0")
(command "_insert" "blkcooledsinglenanobeam7" "2240,900" "1" "1" "180")
(command "_block" "blkyjunction7" "2240,900" yjunction7 "")
(command "_insert" "blkyjunction7" "2240,900" "1" "1" "0")
(command "_insert" "blkyjunction7" "2240,900" "1" "1" "180")
; DRAWING BULGING VEE GROOVE
(command "_layer" "set" "vgroove" "")
(setq coords (list 
(list 2165.415 -605) 
(list 2165.415 0) 
(list 2165.415 0) 
(list 2165.415 1800) 
(list 2165.415 1800) 
(list 2165.415 2405) 
(list 2314.585 2405) 
(list 2314.585 1800) 
(list 2314.585 1800) 
(list 2314.585 0) 
(list 2314.585 0) 
(list 2314.585 -605)))
(apply 'command (append '("pline") coords '("c")))
(command "._fillet" "radius" "0" "._fillet" "P" (entlast))
(command "_layer" "set" "window" "")
(command "_rectangle" "2165.415,-1935" "2314.585,-600")
(command "_rectangle" "2165.415,2400" "2314.585,5300")
(command "_layer" "set" "grid" "")
(command "_rectangle" "2166.415,-1934" "2189.9433,-1909.2133")
(command "_array" "last" "" "R" "75" "3" "25.7867" "24.5283")
(command "_rectangle" "2241,-1934" "2264.5283,-1909.2133")
(command "_array" "last" "" "R" "75" "3" "25.7867" "24.5283")
(command "_rectangle" "2166.415,1" "2189.9433,25.7")
(command "_array" "last" "" "R" "70" "3" "25.7" "24.5283")
(command "_rectangle" "2241,1" "2264.5283,25.7")
(command "_array" "last" "" "R" "70" "3" "25.7" "24.5283")
(command "_rectangle" "2166.415,1801" "2189.9433,1825.9185")
(command "_array" "last" "" "R" "135" "3" "25.9185" "24.5283")
(command "_rectangle" "2241,1801" "2264.5283,1825.9185")
(command "_array" "last" "" "R" "135" "3" "25.9185" "24.5283")
(command "_layer" "set" "vgrooveFDA" "")
(command "_rectangle" "2314.585,-2233" "2165.415,-1933")
(command "_layer" "set" "nitride" "")
(command "_layer" "set" "holes" "")
(command "_circle" "2317.085,331.5" "0.5")
(command "_array" "last" "" "R" "379" "1" "3" "2.5")
(command "_circle" "2162.915,331.5" "0.5")
(command "_array" "last" "" "R" "379" "1" "3" "-2.5")
(command "_layer" "set" "nitride" "")
(command "_layer" "set" "window" "")
(command "_layer" "set" "window" "")
(command "_rectangle" "2319.585,0" "2480.415,1800")
(command "._fillet" "radius" "20" "._fillet" "P" (entlast))
(command "_layer" "set" "grid" "")
(command "_rectangle" "2320.585,1" "2342.4179,25.7")
(command "_array" "last" "" "R" "70" "7" "25.7" "22.8329")
(command "_layer" "set" "nitride" "")
; DRAWING REGION LAYER
(command "_layer" "set" "regionLayer7" "")
(command "_rectangle" "2160,-460" "2320,2260")
(command "_layer" "set" "nitride" "")
(setq coupler7 nil)
(setq singlenanobeam7 nil)
(setq anglednodearray7 nil)
(setq cooledsinglenanobeam7 nil)
(setq yjunction7 nil)
; DEVICE #8
(command "_layer" "set" "window" "")
(command "_circle" "2472.915,-415" "5")
(command "_circle" "2472.915,-402.5" "5")
(command "_circle" "2472.915,-390" "5")
(command "_circle" "2472.915,-377.5" "5")
(command "_circle" "2460.415,-415" "5")
(command "_circle" "2460.415,-402.5" "5")
(command "_circle" "2460.415,-390" "5")
(command "_circle" "2460.415,-377.5" "5")
(command "_layer" "set" "nitride" "")
(setq currobj nil)
(setq currobj (ssadd))
; DRAWING COUPLER
(setq coords (list 
(list 2560.0615 -415) 
(list 2560.0615 -413) 
(list 2633.585 -413) 
(list 2633.585 -413) 
(list 2633.9677 -413.0761) 
(list 2634.2921 -413.2929) 
(list 2634.5089 -413.6173) 
(list 2634.585 -414) 
(list 2634.585 -411.8) 
(list 2634.585 -411.8) 
(list 2634.5089 -412.1827) 
(list 2634.2921 -412.5071) 
(list 2633.9677 -412.7239) 
(list 2633.585 -412.8) 
(list 2560.0615 -412.8) 
(list 2560.0615 -410.8) 
(list 2559.9385 -410.8) 
(list 2559.9385 -412.8) 
(list 2486.415 -412.8) 
(list 2486.0323 -412.7239) 
(list 2485.7079 -412.5071) 
(list 2485.4911 -412.1827) 
(list 2485.415 -411.8) 
(list 2485.415 -411.8) 
(list 2485.415 -414) 
(list 2485.4911 -413.6173) 
(list 2485.7079 -413.2929) 
(list 2486.0323 -413.0761) 
(list 2486.415 -413) 
(list 2486.415 -413) 
(list 2559.9385 -413) 
(list 2559.9385 -415)))
(apply 'command (append '("pline") coords '("c")))
(setq currobj (ssadd (entlast) currobj))
(command "._fillet" "radius" "0.3" "._fillet" "P" (entlast))
(command "_layer" "set" "holes" "")
(command "_circle" "2560,-412.9" "0.113")
(setq currobj (ssadd (entlast) currobj))
(command "_layer" "set" "nitride" "")
(command "_layer" "set" "text" "")
(command "_circle" "2559.2,-415" "0.075")
(command "_circle" "2559.2,-414.7" "0.075")
(command "_circle" "2559.2,-414.4" "0.075")
(command "_circle" "2558.9,-415" "0.075")
(command "_circle" "2558.9,-414.7" "0.075")
(command "_circle" "2558.9,-414.4" "0.075")
(command "_circle" "2558.6,-415" "0.075")
(command "_circle" "2558.6,-414.7" "0.075")
(command "_circle" "2558.6,-414.4" "0.075")
(command "_layer" "set" "nitride" "")
(command "_layer" "set" "prebias" "")
(command "_rectangle" "2485.415,-414" "2634.585,-411.8")
(setq currobj (ssadd (entlast) currobj))
(command "_rectangle" "2559.9385,-415" "2560.0615,-410.8")
(setq currobj (ssadd (entlast) currobj))
(command "_layer" "set" "nitride" "")
(setq coupler8 currobj)
(setq currobj nil)
(setq currobj (ssadd))
; DRAWING SINGLE NANOBEAM
(setq coords (list 
(list 2560.0615 -410.8) 
(list 2560.0615 -409.1417) 
(list 2560.0615 -407.4833) 
(list 2560.0615 -405.825) 
(list 2560.0615 -404.1667) 
(list 2560.0615 -402.5083) 
(list 2560.0615 -400.85) 
(list 2560.0615 -399.1917) 
(list 2560.0615 -397.5333) 
(list 2560.0616 -395.875) 
(list 2560.0616 -394.2167) 
(list 2560.0616 -392.5583) 
(list 2560.0616 -390.9) 
(list 2560.0617 -389.2417) 
(list 2560.0617 -387.5833) 
(list 2560.0617 -385.925) 
(list 2560.0618 -384.2667) 
(list 2560.0619 -382.6083) 
(list 2560.0619 -380.95) 
(list 2560.062 -379.2917) 
(list 2560.0621 -377.6333) 
(list 2560.0622 -375.975) 
(list 2560.0623 -374.3167) 
(list 2560.0624 -372.6583) 
(list 2560.0625 -371) 
(list 2560.0626 -369.3417) 
(list 2560.0628 -367.6833) 
(list 2560.0629 -366.025) 
(list 2560.0631 -364.3667) 
(list 2560.0632 -362.7083) 
(list 2560.0634 -361.05) 
(list 2560.0636 -359.3917) 
(list 2560.0638 -357.7333) 
(list 2560.0641 -356.075) 
(list 2560.0643 -354.4167) 
(list 2560.0646 -352.7583) 
(list 2560.0648 -351.1) 
(list 2560.0651 -349.4417) 
(list 2560.0654 -347.7833) 
(list 2560.0657 -346.125) 
(list 2560.0661 -344.4667) 
(list 2560.0664 -342.8083) 
(list 2560.0668 -341.15) 
(list 2560.0672 -339.4917) 
(list 2560.0676 -337.8333) 
(list 2560.068 -336.175) 
(list 2560.0685 -334.5167) 
(list 2560.0689 -332.8583) 
(list 2560.0694 -331.2) 
(list 2560.0699 -329.5417) 
(list 2560.0704 -327.8833) 
(list 2560.071 -326.225) 
(list 2560.0715 -324.5667) 
(list 2560.0721 -322.9083) 
(list 2560.0728 -321.25) 
(list 2560.0734 -319.5917) 
(list 2560.0741 -317.9333) 
(list 2560.0747 -316.275) 
(list 2560.0754 -314.6167) 
(list 2560.0762 -312.9583) 
(list 2560.0769 -311.3) 
(list 2560.0777 -309.6417) 
(list 2560.0785 -307.9833) 
(list 2560.0794 -306.325) 
(list 2560.0802 -304.6667) 
(list 2560.0811 -303.0083) 
(list 2560.082 -301.35) 
(list 2560.083 -299.6917) 
(list 2560.084 -298.0333) 
(list 2560.085 -296.375) 
(list 2560.086 -294.7167) 
(list 2560.0871 -293.0583) 
(list 2560.0882 -291.4) 
(list 2560.0893 -289.7417) 
(list 2560.0905 -288.0833) 
(list 2560.0917 -286.425) 
(list 2560.0929 -284.7667) 
(list 2560.0941 -283.1083) 
(list 2560.0954 -281.45) 
(list 2560.0967 -279.7917) 
(list 2560.0981 -278.1333) 
(list 2560.0995 -276.475) 
(list 2560.1009 -274.8167) 
(list 2560.1024 -273.1583) 
(list 2560.1039 -271.5) 
(list 2560.1054 -269.8417) 
(list 2560.107 -268.1833) 
(list 2560.1086 -266.525) 
(list 2560.1102 -264.8667) 
(list 2560.1119 -263.2083) 
(list 2560.1136 -261.55) 
(list 2560.1154 -259.8917) 
(list 2560.1172 -258.2333) 
(list 2560.119 -256.575) 
(list 2560.1209 -254.9167) 
(list 2560.1228 -253.2583) 
(list 2560.1247 -251.6) 
(list 2560.1267 -249.9417) 
(list 2560.1288 -248.2833) 
(list 2560.1308 -246.625) 
(list 2560.133 -244.9667) 
(list 2560.1351 -243.3083) 
(list 2560.1373 -241.65) 
(list 2560.1396 -239.9917) 
(list 2560.1419 -238.3333) 
(list 2560.1442 -236.675) 
(list 2560.1466 -235.0167) 
(list 2560.1491 -233.3583) 
(list 2560.1515 -231.7) 
(list 2560.1541 -230.0417) 
(list 2560.1566 -228.3833) 
(list 2560.1592 -226.725) 
(list 2560.1619 -225.0667) 
(list 2560.1646 -223.4083) 
(list 2560.1674 -221.75) 
(list 2560.1702 -220.0917) 
(list 2560.1731 -218.4333) 
(list 2560.176 -216.775) 
(list 2560.1789 -215.1167) 
(list 2560.1819 -213.4583) 
(list 2560.185 -211.8) 
(list 2559.815 -211.8) 
(list 2559.8181 -213.4583) 
(list 2559.8211 -215.1167) 
(list 2559.824 -216.775) 
(list 2559.8269 -218.4333) 
(list 2559.8298 -220.0917) 
(list 2559.8326 -221.75) 
(list 2559.8354 -223.4083) 
(list 2559.8381 -225.0667) 
(list 2559.8408 -226.725) 
(list 2559.8434 -228.3833) 
(list 2559.8459 -230.0417) 
(list 2559.8485 -231.7) 
(list 2559.8509 -233.3583) 
(list 2559.8534 -235.0167) 
(list 2559.8558 -236.675) 
(list 2559.8581 -238.3333) 
(list 2559.8604 -239.9917) 
(list 2559.8627 -241.65) 
(list 2559.8649 -243.3083) 
(list 2559.867 -244.9667) 
(list 2559.8692 -246.625) 
(list 2559.8712 -248.2833) 
(list 2559.8733 -249.9417) 
(list 2559.8753 -251.6) 
(list 2559.8772 -253.2583) 
(list 2559.8791 -254.9167) 
(list 2559.881 -256.575) 
(list 2559.8828 -258.2333) 
(list 2559.8846 -259.8917) 
(list 2559.8864 -261.55) 
(list 2559.8881 -263.2083) 
(list 2559.8898 -264.8667) 
(list 2559.8914 -266.525) 
(list 2559.893 -268.1833) 
(list 2559.8946 -269.8417) 
(list 2559.8961 -271.5) 
(list 2559.8976 -273.1583) 
(list 2559.8991 -274.8167) 
(list 2559.9005 -276.475) 
(list 2559.9019 -278.1333) 
(list 2559.9033 -279.7917) 
(list 2559.9046 -281.45) 
(list 2559.9059 -283.1083) 
(list 2559.9071 -284.7667) 
(list 2559.9083 -286.425) 
(list 2559.9095 -288.0833) 
(list 2559.9107 -289.7417) 
(list 2559.9118 -291.4) 
(list 2559.9129 -293.0583) 
(list 2559.914 -294.7167) 
(list 2559.915 -296.375) 
(list 2559.916 -298.0333) 
(list 2559.917 -299.6917) 
(list 2559.918 -301.35) 
(list 2559.9189 -303.0083) 
(list 2559.9198 -304.6667) 
(list 2559.9206 -306.325) 
(list 2559.9215 -307.9833) 
(list 2559.9223 -309.6417) 
(list 2559.9231 -311.3) 
(list 2559.9238 -312.9583) 
(list 2559.9246 -314.6167) 
(list 2559.9253 -316.275) 
(list 2559.9259 -317.9333) 
(list 2559.9266 -319.5917) 
(list 2559.9272 -321.25) 
(list 2559.9279 -322.9083) 
(list 2559.9285 -324.5667) 
(list 2559.929 -326.225) 
(list 2559.9296 -327.8833) 
(list 2559.9301 -329.5417) 
(list 2559.9306 -331.2) 
(list 2559.9311 -332.8583) 
(list 2559.9315 -334.5167) 
(list 2559.932 -336.175) 
(list 2559.9324 -337.8333) 
(list 2559.9328 -339.4917) 
(list 2559.9332 -341.15) 
(list 2559.9336 -342.8083) 
(list 2559.9339 -344.4667) 
(list 2559.9343 -346.125) 
(list 2559.9346 -347.7833) 
(list 2559.9349 -349.4417) 
(list 2559.9352 -351.1) 
(list 2559.9354 -352.7583) 
(list 2559.9357 -354.4167) 
(list 2559.9359 -356.075) 
(list 2559.9362 -357.7333) 
(list 2559.9364 -359.3917) 
(list 2559.9366 -361.05) 
(list 2559.9368 -362.7083) 
(list 2559.9369 -364.3667) 
(list 2559.9371 -366.025) 
(list 2559.9372 -367.6833) 
(list 2559.9374 -369.3417) 
(list 2559.9375 -371) 
(list 2559.9376 -372.6583) 
(list 2559.9377 -374.3167) 
(list 2559.9378 -375.975) 
(list 2559.9379 -377.6333) 
(list 2559.938 -379.2917) 
(list 2559.9381 -380.95) 
(list 2559.9381 -382.6083) 
(list 2559.9382 -384.2667) 
(list 2559.9383 -385.925) 
(list 2559.9383 -387.5833) 
(list 2559.9383 -389.2417) 
(list 2559.9384 -390.9) 
(list 2559.9384 -392.5583) 
(list 2559.9384 -394.2167) 
(list 2559.9384 -395.875) 
(list 2559.9385 -397.5333) 
(list 2559.9385 -399.1917) 
(list 2559.9385 -400.85) 
(list 2559.9385 -402.5083) 
(list 2559.9385 -404.1667) 
(list 2559.9385 -405.825) 
(list 2559.9385 -407.4833) 
(list 2559.9385 -409.1417) 
(list 2559.9385 -410.8)))
(apply 'command (append '("pline") coords '("c")))
(setq currobj (ssadd (entlast) currobj))
(command "_layer" "set" "prebias" "")
(command "_rectangle" "2559.815,-410.8" "2560.185,-211.8")
(setq currobj (ssadd (entlast) currobj))
(command "_layer" "set" "nitride" "")
(setq singlenanobeam8 currobj)
(setq currobj nil)
(setq currobj (ssadd))
; DRAWING NODE ARRAY
(setq coords (list 
(list 2560.185 -211.8) 
(list 2560.5625 -201.8) 
(list 2560.5625 -201.8) 
(list 2560.5625 -200.8) 
(list 2634.585 -212.6864) 
(list 2634.585 -207.7434) 
(list 2560.5625 -197.357) 
(list 2560.5625 -196.357) 
(list 2560.5625 -196.357) 
(list 2560.2625 -186.357) 
(list 2559.7375 -186.357) 
(list 2559.4375 -196.357) 
(list 2559.4375 -196.357) 
(list 2559.4375 -197.357) 
(list 2485.415 -207.7434) 
(list 2485.415 -212.6864) 
(list 2559.4375 -200.8) 
(list 2559.4375 -201.8) 
(list 2559.4375 -201.8) 
(list 2559.815 -211.8)))
(apply 'command (append '("pline") coords '("c")))
(setq currobj (ssadd (entlast) currobj))
(command "_layer" "set" "prebias" "")
(setq coords (list 
(list 2559.4375 -212.6864) 
(list 2559.4375 -200.8) 
(list 2485.415 -212.6864) 
(list 2485.415 -207.7434) 
(list 2559.4375 -197.357) 
(list 2559.4375 -186.357) 
(list 2560.5625 -186.357) 
(list 2560.5625 -197.357) 
(list 2634.585 -207.7434) 
(list 2634.585 -212.6864) 
(list 2560.5625 -200.8) 
(list 2560.5625 -212.6864)))
(apply 'command (append '("pline") coords '("c")))
(setq currobj (ssadd (entlast) currobj))
(command "_layer" "set" "nitride" "")
(command "_layer" "set" "fda1" "")
(setq coords (list 
(list 2560.5625 -200.657) 
(list 2634.585 -212.5434) 
(list 2634.585 -212.3664) 
(list 2560.5625 -200.58)))
(apply 'command (append '("pline") coords '("c")))
(setq currobj (ssadd (entlast) currobj))
(setq coords (list 
(list 2560.5625 -200.437) 
(list 2634.585 -212.2234) 
(list 2634.585 -212.0464) 
(list 2560.5625 -200.36)))
(apply 'command (append '("pline") coords '("c")))
(setq currobj (ssadd (entlast) currobj))
(setq coords (list 
(list 2560.5625 -200.217) 
(list 2634.585 -211.9034) 
(list 2634.585 -211.7264) 
(list 2560.5625 -200.14)))
(apply 'command (append '("pline") coords '("c")))
(setq currobj (ssadd (entlast) currobj))
(setq coords (list 
(list 2560.5625 -199.997) 
(list 2634.585 -211.5834) 
(list 2634.585 -211.4064) 
(list 2560.5625 -199.92)))
(apply 'command (append '("pline") coords '("c")))
(setq currobj (ssadd (entlast) currobj))
(setq coords (list 
(list 2560.5625 -199.777) 
(list 2634.585 -211.2634) 
(list 2634.585 -211.0864) 
(list 2560.5625 -199.7)))
(apply 'command (append '("pline") coords '("c")))
(setq currobj (ssadd (entlast) currobj))
(setq coords (list 
(list 2560.5625 -199.557) 
(list 2634.585 -210.9434) 
(list 2634.585 -210.7664) 
(list 2560.5625 -199.48)))
(apply 'command (append '("pline") coords '("c")))
(setq currobj (ssadd (entlast) currobj))
(setq coords (list 
(list 2560.5625 -199.337) 
(list 2634.585 -210.6234) 
(list 2634.585 -210.4464) 
(list 2560.5625 -199.26)))
(apply 'command (append '("pline") coords '("c")))
(setq currobj (ssadd (entlast) currobj))
(setq coords (list 
(list 2560.5625 -199.117) 
(list 2634.585 -210.3034) 
(list 2634.585 -210.1264) 
(list 2560.5625 -199.04)))
(apply 'command (append '("pline") coords '("c")))
(setq currobj (ssadd (entlast) currobj))
(setq coords (list 
(list 2560.5625 -198.897) 
(list 2634.585 -209.9834) 
(list 2634.585 -209.8064) 
(list 2560.5625 -198.82)))
(apply 'command (append '("pline") coords '("c")))
(setq currobj (ssadd (entlast) currobj))
(setq coords (list 
(list 2560.5625 -198.677) 
(list 2634.585 -209.6634) 
(list 2634.585 -209.4864) 
(list 2560.5625 -198.6)))
(apply 'command (append '("pline") coords '("c")))
(setq currobj (ssadd (entlast) currobj))
(setq coords (list 
(list 2560.5625 -198.457) 
(list 2634.585 -209.3434) 
(list 2634.585 -209.1664) 
(list 2560.5625 -198.38)))
(apply 'command (append '("pline") coords '("c")))
(setq currobj (ssadd (entlast) currobj))
(setq coords (list 
(list 2560.5625 -198.237) 
(list 2634.585 -209.0234) 
(list 2634.585 -208.8464) 
(list 2560.5625 -198.16)))
(apply 'command (append '("pline") coords '("c")))
(setq currobj (ssadd (entlast) currobj))
(setq coords (list 
(list 2560.5625 -198.017) 
(list 2634.585 -208.7034) 
(list 2634.585 -208.5264) 
(list 2560.5625 -197.94)))
(apply 'command (append '("pline") coords '("c")))
(setq currobj (ssadd (entlast) currobj))
(setq coords (list 
(list 2560.5625 -197.797) 
(list 2634.585 -208.3834) 
(list 2634.585 -208.2064) 
(list 2560.5625 -197.72)))
(apply 'command (append '("pline") coords '("c")))
(setq currobj (ssadd (entlast) currobj))
(setq coords (list 
(list 2560.5625 -197.577) 
(list 2634.585 -208.0634) 
(list 2634.585 -207.8864) 
(list 2560.5625 -197.5)))
(apply 'command (append '("pline") coords '("c")))
(setq currobj (ssadd (entlast) currobj))
(setq coords (list 
(list 2559.4375 -197.5) 
(list 2485.415 -207.8864) 
(list 2485.415 -208.0634) 
(list 2559.4375 -197.577)))
(apply 'command (append '("pline") coords '("c")))
(setq currobj (ssadd (entlast) currobj))
(setq coords (list 
(list 2559.4375 -197.72) 
(list 2485.415 -208.2064) 
(list 2485.415 -208.3834) 
(list 2559.4375 -197.797)))
(apply 'command (append '("pline") coords '("c")))
(setq currobj (ssadd (entlast) currobj))
(setq coords (list 
(list 2559.4375 -197.94) 
(list 2485.415 -208.5264) 
(list 2485.415 -208.7034) 
(list 2559.4375 -198.017)))
(apply 'command (append '("pline") coords '("c")))
(setq currobj (ssadd (entlast) currobj))
(setq coords (list 
(list 2559.4375 -198.16) 
(list 2485.415 -208.8464) 
(list 2485.415 -209.0234) 
(list 2559.4375 -198.237)))
(apply 'command (append '("pline") coords '("c")))
(setq currobj (ssadd (entlast) currobj))
(setq coords (list 
(list 2559.4375 -198.38) 
(list 2485.415 -209.1664) 
(list 2485.415 -209.3434) 
(list 2559.4375 -198.457)))
(apply 'command (append '("pline") coords '("c")))
(setq currobj (ssadd (entlast) currobj))
(setq coords (list 
(list 2559.4375 -198.6) 
(list 2485.415 -209.4864) 
(list 2485.415 -209.6634) 
(list 2559.4375 -198.677)))
(apply 'command (append '("pline") coords '("c")))
(setq currobj (ssadd (entlast) currobj))
(setq coords (list 
(list 2559.4375 -198.82) 
(list 2485.415 -209.8064) 
(list 2485.415 -209.9834) 
(list 2559.4375 -198.897)))
(apply 'command (append '("pline") coords '("c")))
(setq currobj (ssadd (entlast) currobj))
(setq coords (list 
(list 2559.4375 -199.04) 
(list 2485.415 -210.1264) 
(list 2485.415 -210.3034) 
(list 2559.4375 -199.117)))
(apply 'command (append '("pline") coords '("c")))
(setq currobj (ssadd (entlast) currobj))
(setq coords (list 
(list 2559.4375 -199.26) 
(list 2485.415 -210.4464) 
(list 2485.415 -210.6234) 
(list 2559.4375 -199.337)))
(apply 'command (append '("pline") coords '("c")))
(setq currobj (ssadd (entlast) currobj))
(setq coords (list 
(list 2559.4375 -199.48) 
(list 2485.415 -210.7664) 
(list 2485.415 -210.9434) 
(list 2559.4375 -199.557)))
(apply 'command (append '("pline") coords '("c")))
(setq currobj (ssadd (entlast) currobj))
(setq coords (list 
(list 2559.4375 -199.7) 
(list 2485.415 -211.0864) 
(list 2485.415 -211.2634) 
(list 2559.4375 -199.777)))
(apply 'command (append '("pline") coords '("c")))
(setq currobj (ssadd (entlast) currobj))
(setq coords (list 
(list 2559.4375 -199.92) 
(list 2485.415 -211.4064) 
(list 2485.415 -211.5834) 
(list 2559.4375 -199.997)))
(apply 'command (append '("pline") coords '("c")))
(setq currobj (ssadd (entlast) currobj))
(setq coords (list 
(list 2559.4375 -200.14) 
(list 2485.415 -211.7264) 
(list 2485.415 -211.9034) 
(list 2559.4375 -200.217)))
(apply 'command (append '("pline") coords '("c")))
(setq currobj (ssadd (entlast) currobj))
(setq coords (list 
(list 2559.4375 -200.36) 
(list 2485.415 -212.0464) 
(list 2485.415 -212.2234) 
(list 2559.4375 -200.437)))
(apply 'command (append '("pline") coords '("c")))
(setq currobj (ssadd (entlast) currobj))
(setq coords (list 
(list 2559.4375 -200.58) 
(list 2485.415 -212.3664) 
(list 2485.415 -212.5434) 
(list 2559.4375 -200.657)))
(apply 'command (append '("pline") coords '("c")))
(setq currobj (ssadd (entlast) currobj))
(command "_layer" "set" "nitride" "")
(command "_layer" "set" "text" "")
(command "_circle" "2558.985,-211.8" "0.075")
(command "_circle" "2558.985,-211.5" "0.075")
(command "_circle" "2558.985,-211.2" "0.075")
(command "_circle" "2558.985,-210.9" "0.075")
(command "_circle" "2558.985,-210.6" "0.075")
(command "_circle" "2558.685,-211.8" "0.075")
(command "_circle" "2558.685,-211.5" "0.075")
(command "_circle" "2558.685,-211.2" "0.075")
(command "_circle" "2558.685,-210.9" "0.075")
(command "_circle" "2558.685,-210.6" "0.075")
(command "_circle" "2558.385,-211.8" "0.075")
(command "_circle" "2558.385,-211.5" "0.075")
(command "_circle" "2558.385,-211.2" "0.075")
(command "_circle" "2558.385,-210.9" "0.075")
(command "_circle" "2558.385,-210.6" "0.075")
(command "_circle" "2558.085,-211.8" "0.075")
(command "_circle" "2558.085,-211.5" "0.075")
(command "_circle" "2558.085,-211.2" "0.075")
(command "_circle" "2558.085,-210.9" "0.075")
(command "_circle" "2558.085,-210.6" "0.075")
(command "_circle" "2557.785,-211.8" "0.075")
(command "_circle" "2557.785,-211.5" "0.075")
(command "_circle" "2557.785,-211.2" "0.075")
(command "_circle" "2557.785,-210.9" "0.075")
(command "_circle" "2557.785,-210.6" "0.075")
(command "_layer" "set" "nitride" "")
(setq anglednodearray8 currobj)
(setq currobj nil)
(setq currobj (ssadd))
; DRAWING COOLED SINGLE NANOBEAM
(setq coords (list 
(list 2560.2625 -186.357) 
(list 2560.2625 -181.357) 
(list 2559.7375 -181.357) 
(list 2559.7375 -186.357)))
(apply 'command (append '("pline") coords '("c")))
(setq currobj (ssadd (entlast) currobj))
(command "_layer" "set" "prebias" "")
(command "_rectangle" "2559.7375,-186.357" "2560.2625,-181.357")
(setq currobj (ssadd (entlast) currobj))
(command "_layer" "set" "nitride" "")
(setq coords (list 
(list 2560.2625 -181.357) 
(list 2560.5625 -171.357) 
(list 2560.5625 -171.357) 
(list 2560.5625 -170.357) 
(list 2634.585 -171.107) 
(list 2634.585 -166.164) 
(list 2560.5625 -166.914) 
(list 2560.5625 -165.914) 
(list 2560.5625 -165.914) 
(list 2560.2625 -155.914) 
(list 2559.7375 -155.914) 
(list 2559.4375 -165.914) 
(list 2559.4375 -165.914) 
(list 2559.4375 -166.914) 
(list 2485.415 -166.164) 
(list 2485.415 -171.107) 
(list 2559.4375 -170.357) 
(list 2559.4375 -171.357) 
(list 2559.4375 -171.357) 
(list 2559.7375 -181.357)))
(apply 'command (append '("pline") coords '("c")))
(setq currobj (ssadd (entlast) currobj))
(command "_layer" "set" "prebias" "")
(setq coords (list 
(list 2559.4375 -181.357) 
(list 2559.4375 -170.357) 
(list 2485.415 -171.107) 
(list 2485.415 -166.164) 
(list 2559.4375 -166.914) 
(list 2559.4375 -155.914) 
(list 2560.5625 -155.914) 
(list 2560.5625 -166.914) 
(list 2634.585 -166.164) 
(list 2634.585 -171.107) 
(list 2560.5625 -170.357) 
(list 2560.5625 -181.357)))
(apply 'command (append '("pline") coords '("c")))
(setq currobj (ssadd (entlast) currobj))
(command "_layer" "set" "nitride" "")
(command "_layer" "set" "fda1" "")
(setq coords (list 
(list 2560.5625 -170.214) 
(list 2634.585 -170.964) 
(list 2634.585 -170.787) 
(list 2560.5625 -170.137)))
(apply 'command (append '("pline") coords '("c")))
(setq currobj (ssadd (entlast) currobj))
(setq coords (list 
(list 2560.5625 -169.994) 
(list 2634.585 -170.644) 
(list 2634.585 -170.467) 
(list 2560.5625 -169.917)))
(apply 'command (append '("pline") coords '("c")))
(setq currobj (ssadd (entlast) currobj))
(setq coords (list 
(list 2560.5625 -169.774) 
(list 2634.585 -170.324) 
(list 2634.585 -170.147) 
(list 2560.5625 -169.697)))
(apply 'command (append '("pline") coords '("c")))
(setq currobj (ssadd (entlast) currobj))
(setq coords (list 
(list 2560.5625 -169.554) 
(list 2634.585 -170.004) 
(list 2634.585 -169.827) 
(list 2560.5625 -169.477)))
(apply 'command (append '("pline") coords '("c")))
(setq currobj (ssadd (entlast) currobj))
(setq coords (list 
(list 2560.5625 -169.334) 
(list 2634.585 -169.684) 
(list 2634.585 -169.507) 
(list 2560.5625 -169.257)))
(apply 'command (append '("pline") coords '("c")))
(setq currobj (ssadd (entlast) currobj))
(setq coords (list 
(list 2560.5625 -169.114) 
(list 2634.585 -169.364) 
(list 2634.585 -169.187) 
(list 2560.5625 -169.037)))
(apply 'command (append '("pline") coords '("c")))
(setq currobj (ssadd (entlast) currobj))
(setq coords (list 
(list 2560.5625 -168.894) 
(list 2634.585 -169.044) 
(list 2634.585 -168.867) 
(list 2560.5625 -168.817)))
(apply 'command (append '("pline") coords '("c")))
(setq currobj (ssadd (entlast) currobj))
(setq coords (list 
(list 2560.5625 -168.674) 
(list 2634.585 -168.724) 
(list 2634.585 -168.547) 
(list 2560.5625 -168.597)))
(apply 'command (append '("pline") coords '("c")))
(setq currobj (ssadd (entlast) currobj))
(setq coords (list 
(list 2560.5625 -168.454) 
(list 2634.585 -168.404) 
(list 2634.585 -168.227) 
(list 2560.5625 -168.377)))
(apply 'command (append '("pline") coords '("c")))
(setq currobj (ssadd (entlast) currobj))
(setq coords (list 
(list 2560.5625 -168.234) 
(list 2634.585 -168.084) 
(list 2634.585 -167.907) 
(list 2560.5625 -168.157)))
(apply 'command (append '("pline") coords '("c")))
(setq currobj (ssadd (entlast) currobj))
(setq coords (list 
(list 2560.5625 -168.014) 
(list 2634.585 -167.764) 
(list 2634.585 -167.587) 
(list 2560.5625 -167.937)))
(apply 'command (append '("pline") coords '("c")))
(setq currobj (ssadd (entlast) currobj))
(setq coords (list 
(list 2560.5625 -167.794) 
(list 2634.585 -167.444) 
(list 2634.585 -167.267) 
(list 2560.5625 -167.717)))
(apply 'command (append '("pline") coords '("c")))
(setq currobj (ssadd (entlast) currobj))
(setq coords (list 
(list 2560.5625 -167.574) 
(list 2634.585 -167.124) 
(list 2634.585 -166.947) 
(list 2560.5625 -167.497)))
(apply 'command (append '("pline") coords '("c")))
(setq currobj (ssadd (entlast) currobj))
(setq coords (list 
(list 2560.5625 -167.354) 
(list 2634.585 -166.804) 
(list 2634.585 -166.627) 
(list 2560.5625 -167.277)))
(apply 'command (append '("pline") coords '("c")))
(setq currobj (ssadd (entlast) currobj))
(setq coords (list 
(list 2560.5625 -167.134) 
(list 2634.585 -166.484) 
(list 2634.585 -166.307) 
(list 2560.5625 -167.057)))
(apply 'command (append '("pline") coords '("c")))
(setq currobj (ssadd (entlast) currobj))
(setq coords (list 
(list 2559.4375 -167.057) 
(list 2485.415 -166.307) 
(list 2485.415 -166.484) 
(list 2559.4375 -167.134)))
(apply 'command (append '("pline") coords '("c")))
(setq currobj (ssadd (entlast) currobj))
(setq coords (list 
(list 2559.4375 -167.277) 
(list 2485.415 -166.627) 
(list 2485.415 -166.804) 
(list 2559.4375 -167.354)))
(apply 'command (append '("pline") coords '("c")))
(setq currobj (ssadd (entlast) currobj))
(setq coords (list 
(list 2559.4375 -167.497) 
(list 2485.415 -166.947) 
(list 2485.415 -167.124) 
(list 2559.4375 -167.574)))
(apply 'command (append '("pline") coords '("c")))
(setq currobj (ssadd (entlast) currobj))
(setq coords (list 
(list 2559.4375 -167.717) 
(list 2485.415 -167.267) 
(list 2485.415 -167.444) 
(list 2559.4375 -167.794)))
(apply 'command (append '("pline") coords '("c")))
(setq currobj (ssadd (entlast) currobj))
(setq coords (list 
(list 2559.4375 -167.937) 
(list 2485.415 -167.587) 
(list 2485.415 -167.764) 
(list 2559.4375 -168.014)))
(apply 'command (append '("pline") coords '("c")))
(setq currobj (ssadd (entlast) currobj))
(setq coords (list 
(list 2559.4375 -168.157) 
(list 2485.415 -167.907) 
(list 2485.415 -168.084) 
(list 2559.4375 -168.234)))
(apply 'command (append '("pline") coords '("c")))
(setq currobj (ssadd (entlast) currobj))
(setq coords (list 
(list 2559.4375 -168.377) 
(list 2485.415 -168.227) 
(list 2485.415 -168.404) 
(list 2559.4375 -168.454)))
(apply 'command (append '("pline") coords '("c")))
(setq currobj (ssadd (entlast) currobj))
(setq coords (list 
(list 2559.4375 -168.597) 
(list 2485.415 -168.547) 
(list 2485.415 -168.724) 
(list 2559.4375 -168.674)))
(apply 'command (append '("pline") coords '("c")))
(setq currobj (ssadd (entlast) currobj))
(setq coords (list 
(list 2559.4375 -168.817) 
(list 2485.415 -168.867) 
(list 2485.415 -169.044) 
(list 2559.4375 -168.894)))
(apply 'command (append '("pline") coords '("c")))
(setq currobj (ssadd (entlast) currobj))
(setq coords (list 
(list 2559.4375 -169.037) 
(list 2485.415 -169.187) 
(list 2485.415 -169.364) 
(list 2559.4375 -169.114)))
(apply 'command (append '("pline") coords '("c")))
(setq currobj (ssadd (entlast) currobj))
(setq coords (list 
(list 2559.4375 -169.257) 
(list 2485.415 -169.507) 
(list 2485.415 -169.684) 
(list 2559.4375 -169.334)))
(apply 'command (append '("pline") coords '("c")))
(setq currobj (ssadd (entlast) currobj))
(setq coords (list 
(list 2559.4375 -169.477) 
(list 2485.415 -169.827) 
(list 2485.415 -170.004) 
(list 2559.4375 -169.554)))
(apply 'command (append '("pline") coords '("c")))
(setq currobj (ssadd (entlast) currobj))
(setq coords (list 
(list 2559.4375 -169.697) 
(list 2485.415 -170.147) 
(list 2485.415 -170.324) 
(list 2559.4375 -169.774)))
(apply 'command (append '("pline") coords '("c")))
(setq currobj (ssadd (entlast) currobj))
(setq coords (list 
(list 2559.4375 -169.917) 
(list 2485.415 -170.467) 
(list 2485.415 -170.644) 
(list 2559.4375 -169.994)))
(apply 'command (append '("pline") coords '("c")))
(setq currobj (ssadd (entlast) currobj))
(setq coords (list 
(list 2559.4375 -170.137) 
(list 2485.415 -170.787) 
(list 2485.415 -170.964) 
(list 2559.4375 -170.214)))
(apply 'command (append '("pline") coords '("c")))
(setq currobj (ssadd (entlast) currobj))
(command "_layer" "set" "nitride" "")
(command "_layer" "set" "text" "")
(command "_circle" "2559.0625,-181.357" "0.075")
(command "_circle" "2559.0625,-181.057" "0.075")
(command "_circle" "2559.0625,-180.757" "0.075")
(command "_circle" "2559.0625,-180.457" "0.075")
(command "_circle" "2559.0625,-180.157" "0.075")
(command "_circle" "2558.7625,-181.357" "0.075")
(command "_circle" "2558.7625,-181.057" "0.075")
(command "_circle" "2558.7625,-180.757" "0.075")
(command "_circle" "2558.7625,-180.457" "0.075")
(command "_circle" "2558.7625,-180.157" "0.075")
(command "_circle" "2558.4625,-181.357" "0.075")
(command "_circle" "2558.4625,-181.057" "0.075")
(command "_circle" "2558.4625,-180.757" "0.075")
(command "_circle" "2558.4625,-180.457" "0.075")
(command "_circle" "2558.4625,-180.157" "0.075")
(command "_circle" "2558.1625,-181.357" "0.075")
(command "_circle" "2558.1625,-181.057" "0.075")
(command "_circle" "2558.1625,-180.757" "0.075")
(command "_circle" "2558.1625,-180.457" "0.075")
(command "_circle" "2558.1625,-180.157" "0.075")
(command "_circle" "2557.8625,-181.357" "0.075")
(command "_circle" "2557.8625,-181.057" "0.075")
(command "_circle" "2557.8625,-180.757" "0.075")
(command "_circle" "2557.8625,-180.457" "0.075")
(command "_circle" "2557.8625,-180.157" "0.075")
(command "_layer" "set" "nitride" "")
(setq coords (list 
(list 2560.2625 -155.914) 
(list 2560.2625 -40.2693) 
(list 2559.7375 -40.2693) 
(list 2559.7375 -155.914)))
(apply 'command (append '("pline") coords '("c")))
(setq currobj (ssadd (entlast) currobj))
(command "_layer" "set" "prebias" "")
(command "_rectangle" "2559.7375,-155.914" "2560.2625,-40.2693")
(setq currobj (ssadd (entlast) currobj))
(command "_layer" "set" "nitride" "")
(setq coords (list 
(list 2560.2625 -40.2693) 
(list 2560.5625 -30.2693) 
(list 2560.5625 -30.2693) 
(list 2560.5625 -29.2693) 
(list 2634.585 -30.0193) 
(list 2634.585 -25.0763) 
(list 2560.5625 -25.8263) 
(list 2560.5625 -24.8263) 
(list 2560.5625 -24.8263) 
(list 2560.2625 -14.8263) 
(list 2559.7375 -14.8263) 
(list 2559.4375 -24.8263) 
(list 2559.4375 -24.8263) 
(list 2559.4375 -25.8263) 
(list 2485.415 -25.0763) 
(list 2485.415 -30.0193) 
(list 2559.4375 -29.2693) 
(list 2559.4375 -30.2693) 
(list 2559.4375 -30.2693) 
(list 2559.7375 -40.2693)))
(apply 'command (append '("pline") coords '("c")))
(setq currobj (ssadd (entlast) currobj))
(command "_layer" "set" "prebias" "")
(setq coords (list 
(list 2559.4375 -40.2693) 
(list 2559.4375 -29.2693) 
(list 2485.415 -30.0193) 
(list 2485.415 -25.0763) 
(list 2559.4375 -25.8263) 
(list 2559.4375 -14.8263) 
(list 2560.5625 -14.8263) 
(list 2560.5625 -25.8263) 
(list 2634.585 -25.0763) 
(list 2634.585 -30.0193) 
(list 2560.5625 -29.2693) 
(list 2560.5625 -40.2693)))
(apply 'command (append '("pline") coords '("c")))
(setq currobj (ssadd (entlast) currobj))
(command "_layer" "set" "nitride" "")
(command "_layer" "set" "fda1" "")
(setq coords (list 
(list 2560.5625 -29.1263) 
(list 2634.585 -29.8763) 
(list 2634.585 -29.6993) 
(list 2560.5625 -29.0493)))
(apply 'command (append '("pline") coords '("c")))
(setq currobj (ssadd (entlast) currobj))
(setq coords (list 
(list 2560.5625 -28.9063) 
(list 2634.585 -29.5563) 
(list 2634.585 -29.3793) 
(list 2560.5625 -28.8293)))
(apply 'command (append '("pline") coords '("c")))
(setq currobj (ssadd (entlast) currobj))
(setq coords (list 
(list 2560.5625 -28.6863) 
(list 2634.585 -29.2363) 
(list 2634.585 -29.0593) 
(list 2560.5625 -28.6093)))
(apply 'command (append '("pline") coords '("c")))
(setq currobj (ssadd (entlast) currobj))
(setq coords (list 
(list 2560.5625 -28.4663) 
(list 2634.585 -28.9163) 
(list 2634.585 -28.7393) 
(list 2560.5625 -28.3893)))
(apply 'command (append '("pline") coords '("c")))
(setq currobj (ssadd (entlast) currobj))
(setq coords (list 
(list 2560.5625 -28.2463) 
(list 2634.585 -28.5963) 
(list 2634.585 -28.4193) 
(list 2560.5625 -28.1693)))
(apply 'command (append '("pline") coords '("c")))
(setq currobj (ssadd (entlast) currobj))
(setq coords (list 
(list 2560.5625 -28.0263) 
(list 2634.585 -28.2763) 
(list 2634.585 -28.0993) 
(list 2560.5625 -27.9493)))
(apply 'command (append '("pline") coords '("c")))
(setq currobj (ssadd (entlast) currobj))
(setq coords (list 
(list 2560.5625 -27.8063) 
(list 2634.585 -27.9563) 
(list 2634.585 -27.7793) 
(list 2560.5625 -27.7293)))
(apply 'command (append '("pline") coords '("c")))
(setq currobj (ssadd (entlast) currobj))
(setq coords (list 
(list 2560.5625 -27.5863) 
(list 2634.585 -27.6363) 
(list 2634.585 -27.4593) 
(list 2560.5625 -27.5093)))
(apply 'command (append '("pline") coords '("c")))
(setq currobj (ssadd (entlast) currobj))
(setq coords (list 
(list 2560.5625 -27.3663) 
(list 2634.585 -27.3163) 
(list 2634.585 -27.1393) 
(list 2560.5625 -27.2893)))
(apply 'command (append '("pline") coords '("c")))
(setq currobj (ssadd (entlast) currobj))
(setq coords (list 
(list 2560.5625 -27.1463) 
(list 2634.585 -26.9963) 
(list 2634.585 -26.8193) 
(list 2560.5625 -27.0693)))
(apply 'command (append '("pline") coords '("c")))
(setq currobj (ssadd (entlast) currobj))
(setq coords (list 
(list 2560.5625 -26.9263) 
(list 2634.585 -26.6763) 
(list 2634.585 -26.4993) 
(list 2560.5625 -26.8493)))
(apply 'command (append '("pline") coords '("c")))
(setq currobj (ssadd (entlast) currobj))
(setq coords (list 
(list 2560.5625 -26.7063) 
(list 2634.585 -26.3563) 
(list 2634.585 -26.1793) 
(list 2560.5625 -26.6293)))
(apply 'command (append '("pline") coords '("c")))
(setq currobj (ssadd (entlast) currobj))
(setq coords (list 
(list 2560.5625 -26.4863) 
(list 2634.585 -26.0363) 
(list 2634.585 -25.8593) 
(list 2560.5625 -26.4093)))
(apply 'command (append '("pline") coords '("c")))
(setq currobj (ssadd (entlast) currobj))
(setq coords (list 
(list 2560.5625 -26.2663) 
(list 2634.585 -25.7163) 
(list 2634.585 -25.5393) 
(list 2560.5625 -26.1893)))
(apply 'command (append '("pline") coords '("c")))
(setq currobj (ssadd (entlast) currobj))
(setq coords (list 
(list 2560.5625 -26.0463) 
(list 2634.585 -25.3963) 
(list 2634.585 -25.2193) 
(list 2560.5625 -25.9693)))
(apply 'command (append '("pline") coords '("c")))
(setq currobj (ssadd (entlast) currobj))
(setq coords (list 
(list 2559.4375 -25.9693) 
(list 2485.415 -25.2193) 
(list 2485.415 -25.3963) 
(list 2559.4375 -26.0463)))
(apply 'command (append '("pline") coords '("c")))
(setq currobj (ssadd (entlast) currobj))
(setq coords (list 
(list 2559.4375 -26.1893) 
(list 2485.415 -25.5393) 
(list 2485.415 -25.7163) 
(list 2559.4375 -26.2663)))
(apply 'command (append '("pline") coords '("c")))
(setq currobj (ssadd (entlast) currobj))
(setq coords (list 
(list 2559.4375 -26.4093) 
(list 2485.415 -25.8593) 
(list 2485.415 -26.0363) 
(list 2559.4375 -26.4863)))
(apply 'command (append '("pline") coords '("c")))
(setq currobj (ssadd (entlast) currobj))
(setq coords (list 
(list 2559.4375 -26.6293) 
(list 2485.415 -26.1793) 
(list 2485.415 -26.3563) 
(list 2559.4375 -26.7063)))
(apply 'command (append '("pline") coords '("c")))
(setq currobj (ssadd (entlast) currobj))
(setq coords (list 
(list 2559.4375 -26.8493) 
(list 2485.415 -26.4993) 
(list 2485.415 -26.6763) 
(list 2559.4375 -26.9263)))
(apply 'command (append '("pline") coords '("c")))
(setq currobj (ssadd (entlast) currobj))
(setq coords (list 
(list 2559.4375 -27.0693) 
(list 2485.415 -26.8193) 
(list 2485.415 -26.9963) 
(list 2559.4375 -27.1463)))
(apply 'command (append '("pline") coords '("c")))
(setq currobj (ssadd (entlast) currobj))
(setq coords (list 
(list 2559.4375 -27.2893) 
(list 2485.415 -27.1393) 
(list 2485.415 -27.3163) 
(list 2559.4375 -27.3663)))
(apply 'command (append '("pline") coords '("c")))
(setq currobj (ssadd (entlast) currobj))
(setq coords (list 
(list 2559.4375 -27.5093) 
(list 2485.415 -27.4593) 
(list 2485.415 -27.6363) 
(list 2559.4375 -27.5863)))
(apply 'command (append '("pline") coords '("c")))
(setq currobj (ssadd (entlast) currobj))
(setq coords (list 
(list 2559.4375 -27.7293) 
(list 2485.415 -27.7793) 
(list 2485.415 -27.9563) 
(list 2559.4375 -27.8063)))
(apply 'command (append '("pline") coords '("c")))
(setq currobj (ssadd (entlast) currobj))
(setq coords (list 
(list 2559.4375 -27.9493) 
(list 2485.415 -28.0993) 
(list 2485.415 -28.2763) 
(list 2559.4375 -28.0263)))
(apply 'command (append '("pline") coords '("c")))
(setq currobj (ssadd (entlast) currobj))
(setq coords (list 
(list 2559.4375 -28.1693) 
(list 2485.415 -28.4193) 
(list 2485.415 -28.5963) 
(list 2559.4375 -28.2463)))
(apply 'command (append '("pline") coords '("c")))
(setq currobj (ssadd (entlast) currobj))
(setq coords (list 
(list 2559.4375 -28.3893) 
(list 2485.415 -28.7393) 
(list 2485.415 -28.9163) 
(list 2559.4375 -28.4663)))
(apply 'command (append '("pline") coords '("c")))
(setq currobj (ssadd (entlast) currobj))
(setq coords (list 
(list 2559.4375 -28.6093) 
(list 2485.415 -29.0593) 
(list 2485.415 -29.2363) 
(list 2559.4375 -28.6863)))
(apply 'command (append '("pline") coords '("c")))
(setq currobj (ssadd (entlast) currobj))
(setq coords (list 
(list 2559.4375 -28.8293) 
(list 2485.415 -29.3793) 
(list 2485.415 -29.5563) 
(list 2559.4375 -28.9063)))
(apply 'command (append '("pline") coords '("c")))
(setq currobj (ssadd (entlast) currobj))
(setq coords (list 
(list 2559.4375 -29.0493) 
(list 2485.415 -29.6993) 
(list 2485.415 -29.8763) 
(list 2559.4375 -29.1263)))
(apply 'command (append '("pline") coords '("c")))
(setq currobj (ssadd (entlast) currobj))
(command "_layer" "set" "nitride" "")
(command "_layer" "set" "text" "")
(command "_circle" "2559.0625,-40.2693" "0.075")
(command "_circle" "2559.0625,-39.9693" "0.075")
(command "_circle" "2559.0625,-39.6693" "0.075")
(command "_circle" "2559.0625,-39.3693" "0.075")
(command "_circle" "2559.0625,-39.0693" "0.075")
(command "_circle" "2558.7625,-40.2693" "0.075")
(command "_circle" "2558.7625,-39.9693" "0.075")
(command "_circle" "2558.7625,-39.6693" "0.075")
(command "_circle" "2558.7625,-39.3693" "0.075")
(command "_circle" "2558.7625,-39.0693" "0.075")
(command "_circle" "2558.4625,-40.2693" "0.075")
(command "_circle" "2558.4625,-39.9693" "0.075")
(command "_circle" "2558.4625,-39.6693" "0.075")
(command "_circle" "2558.4625,-39.3693" "0.075")
(command "_circle" "2558.4625,-39.0693" "0.075")
(command "_circle" "2558.1625,-40.2693" "0.075")
(command "_circle" "2558.1625,-39.9693" "0.075")
(command "_circle" "2558.1625,-39.6693" "0.075")
(command "_circle" "2558.1625,-39.3693" "0.075")
(command "_circle" "2558.1625,-39.0693" "0.075")
(command "_circle" "2557.8625,-40.2693" "0.075")
(command "_circle" "2557.8625,-39.9693" "0.075")
(command "_circle" "2557.8625,-39.6693" "0.075")
(command "_circle" "2557.8625,-39.3693" "0.075")
(command "_circle" "2557.8625,-39.0693" "0.075")
(command "_layer" "set" "nitride" "")
(setq coords (list 
(list 2560.2625 -14.8263) 
(list 2560.2625 100.8184) 
(list 2559.7375 100.8184) 
(list 2559.7375 -14.8263)))
(apply 'command (append '("pline") coords '("c")))
(setq currobj (ssadd (entlast) currobj))
(command "_layer" "set" "prebias" "")
(command "_rectangle" "2559.7375,-14.8263" "2560.2625,100.8184")
(setq currobj (ssadd (entlast) currobj))
(command "_layer" "set" "nitride" "")
(setq coords (list 
(list 2560.2625 100.8184) 
(list 2560.5625 110.8184) 
(list 2560.5625 110.8184) 
(list 2560.5625 111.8184) 
(list 2634.585 111.0684) 
(list 2634.585 116.0114) 
(list 2560.5625 115.2614) 
(list 2560.5625 116.2614) 
(list 2560.5625 116.2614) 
(list 2560.2625 126.2614) 
(list 2559.7375 126.2614) 
(list 2559.4375 116.2614) 
(list 2559.4375 116.2614) 
(list 2559.4375 115.2614) 
(list 2485.415 116.0114) 
(list 2485.415 111.0684) 
(list 2559.4375 111.8184) 
(list 2559.4375 110.8184) 
(list 2559.4375 110.8184) 
(list 2559.7375 100.8184)))
(apply 'command (append '("pline") coords '("c")))
(setq currobj (ssadd (entlast) currobj))
(command "_layer" "set" "prebias" "")
(setq coords (list 
(list 2559.4375 100.8184) 
(list 2559.4375 111.8184) 
(list 2485.415 111.0684) 
(list 2485.415 116.0114) 
(list 2559.4375 115.2614) 
(list 2559.4375 126.2614) 
(list 2560.5625 126.2614) 
(list 2560.5625 115.2614) 
(list 2634.585 116.0114) 
(list 2634.585 111.0684) 
(list 2560.5625 111.8184) 
(list 2560.5625 100.8184)))
(apply 'command (append '("pline") coords '("c")))
(setq currobj (ssadd (entlast) currobj))
(command "_layer" "set" "nitride" "")
(command "_layer" "set" "fda1" "")
(setq coords (list 
(list 2560.5625 111.9614) 
(list 2634.585 111.2114) 
(list 2634.585 111.3884) 
(list 2560.5625 112.0384)))
(apply 'command (append '("pline") coords '("c")))
(setq currobj (ssadd (entlast) currobj))
(setq coords (list 
(list 2560.5625 112.1814) 
(list 2634.585 111.5314) 
(list 2634.585 111.7084) 
(list 2560.5625 112.2584)))
(apply 'command (append '("pline") coords '("c")))
(setq currobj (ssadd (entlast) currobj))
(setq coords (list 
(list 2560.5625 112.4014) 
(list 2634.585 111.8514) 
(list 2634.585 112.0284) 
(list 2560.5625 112.4784)))
(apply 'command (append '("pline") coords '("c")))
(setq currobj (ssadd (entlast) currobj))
(setq coords (list 
(list 2560.5625 112.6214) 
(list 2634.585 112.1714) 
(list 2634.585 112.3484) 
(list 2560.5625 112.6984)))
(apply 'command (append '("pline") coords '("c")))
(setq currobj (ssadd (entlast) currobj))
(setq coords (list 
(list 2560.5625 112.8414) 
(list 2634.585 112.4914) 
(list 2634.585 112.6684) 
(list 2560.5625 112.9184)))
(apply 'command (append '("pline") coords '("c")))
(setq currobj (ssadd (entlast) currobj))
(setq coords (list 
(list 2560.5625 113.0614) 
(list 2634.585 112.8114) 
(list 2634.585 112.9884) 
(list 2560.5625 113.1384)))
(apply 'command (append '("pline") coords '("c")))
(setq currobj (ssadd (entlast) currobj))
(setq coords (list 
(list 2560.5625 113.2814) 
(list 2634.585 113.1314) 
(list 2634.585 113.3084) 
(list 2560.5625 113.3584)))
(apply 'command (append '("pline") coords '("c")))
(setq currobj (ssadd (entlast) currobj))
(setq coords (list 
(list 2560.5625 113.5014) 
(list 2634.585 113.4514) 
(list 2634.585 113.6284) 
(list 2560.5625 113.5784)))
(apply 'command (append '("pline") coords '("c")))
(setq currobj (ssadd (entlast) currobj))
(setq coords (list 
(list 2560.5625 113.7214) 
(list 2634.585 113.7714) 
(list 2634.585 113.9484) 
(list 2560.5625 113.7984)))
(apply 'command (append '("pline") coords '("c")))
(setq currobj (ssadd (entlast) currobj))
(setq coords (list 
(list 2560.5625 113.9414) 
(list 2634.585 114.0914) 
(list 2634.585 114.2684) 
(list 2560.5625 114.0184)))
(apply 'command (append '("pline") coords '("c")))
(setq currobj (ssadd (entlast) currobj))
(setq coords (list 
(list 2560.5625 114.1614) 
(list 2634.585 114.4114) 
(list 2634.585 114.5884) 
(list 2560.5625 114.2384)))
(apply 'command (append '("pline") coords '("c")))
(setq currobj (ssadd (entlast) currobj))
(setq coords (list 
(list 2560.5625 114.3814) 
(list 2634.585 114.7314) 
(list 2634.585 114.9084) 
(list 2560.5625 114.4584)))
(apply 'command (append '("pline") coords '("c")))
(setq currobj (ssadd (entlast) currobj))
(setq coords (list 
(list 2560.5625 114.6014) 
(list 2634.585 115.0514) 
(list 2634.585 115.2284) 
(list 2560.5625 114.6784)))
(apply 'command (append '("pline") coords '("c")))
(setq currobj (ssadd (entlast) currobj))
(setq coords (list 
(list 2560.5625 114.8214) 
(list 2634.585 115.3714) 
(list 2634.585 115.5484) 
(list 2560.5625 114.8984)))
(apply 'command (append '("pline") coords '("c")))
(setq currobj (ssadd (entlast) currobj))
(setq coords (list 
(list 2560.5625 115.0414) 
(list 2634.585 115.6914) 
(list 2634.585 115.8684) 
(list 2560.5625 115.1184)))
(apply 'command (append '("pline") coords '("c")))
(setq currobj (ssadd (entlast) currobj))
(setq coords (list 
(list 2559.4375 115.1184) 
(list 2485.415 115.8684) 
(list 2485.415 115.6914) 
(list 2559.4375 115.0414)))
(apply 'command (append '("pline") coords '("c")))
(setq currobj (ssadd (entlast) currobj))
(setq coords (list 
(list 2559.4375 114.8984) 
(list 2485.415 115.5484) 
(list 2485.415 115.3714) 
(list 2559.4375 114.8214)))
(apply 'command (append '("pline") coords '("c")))
(setq currobj (ssadd (entlast) currobj))
(setq coords (list 
(list 2559.4375 114.6784) 
(list 2485.415 115.2284) 
(list 2485.415 115.0514) 
(list 2559.4375 114.6014)))
(apply 'command (append '("pline") coords '("c")))
(setq currobj (ssadd (entlast) currobj))
(setq coords (list 
(list 2559.4375 114.4584) 
(list 2485.415 114.9084) 
(list 2485.415 114.7314) 
(list 2559.4375 114.3814)))
(apply 'command (append '("pline") coords '("c")))
(setq currobj (ssadd (entlast) currobj))
(setq coords (list 
(list 2559.4375 114.2384) 
(list 2485.415 114.5884) 
(list 2485.415 114.4114) 
(list 2559.4375 114.1614)))
(apply 'command (append '("pline") coords '("c")))
(setq currobj (ssadd (entlast) currobj))
(setq coords (list 
(list 2559.4375 114.0184) 
(list 2485.415 114.2684) 
(list 2485.415 114.0914) 
(list 2559.4375 113.9414)))
(apply 'command (append '("pline") coords '("c")))
(setq currobj (ssadd (entlast) currobj))
(setq coords (list 
(list 2559.4375 113.7984) 
(list 2485.415 113.9484) 
(list 2485.415 113.7714) 
(list 2559.4375 113.7214)))
(apply 'command (append '("pline") coords '("c")))
(setq currobj (ssadd (entlast) currobj))
(setq coords (list 
(list 2559.4375 113.5784) 
(list 2485.415 113.6284) 
(list 2485.415 113.4514) 
(list 2559.4375 113.5014)))
(apply 'command (append '("pline") coords '("c")))
(setq currobj (ssadd (entlast) currobj))
(setq coords (list 
(list 2559.4375 113.3584) 
(list 2485.415 113.3084) 
(list 2485.415 113.1314) 
(list 2559.4375 113.2814)))
(apply 'command (append '("pline") coords '("c")))
(setq currobj (ssadd (entlast) currobj))
(setq coords (list 
(list 2559.4375 113.1384) 
(list 2485.415 112.9884) 
(list 2485.415 112.8114) 
(list 2559.4375 113.0614)))
(apply 'command (append '("pline") coords '("c")))
(setq currobj (ssadd (entlast) currobj))
(setq coords (list 
(list 2559.4375 112.9184) 
(list 2485.415 112.6684) 
(list 2485.415 112.4914) 
(list 2559.4375 112.8414)))
(apply 'command (append '("pline") coords '("c")))
(setq currobj (ssadd (entlast) currobj))
(setq coords (list 
(list 2559.4375 112.6984) 
(list 2485.415 112.3484) 
(list 2485.415 112.1714) 
(list 2559.4375 112.6214)))
(apply 'command (append '("pline") coords '("c")))
(setq currobj (ssadd (entlast) currobj))
(setq coords (list 
(list 2559.4375 112.4784) 
(list 2485.415 112.0284) 
(list 2485.415 111.8514) 
(list 2559.4375 112.4014)))
(apply 'command (append '("pline") coords '("c")))
(setq currobj (ssadd (entlast) currobj))
(setq coords (list 
(list 2559.4375 112.2584) 
(list 2485.415 111.7084) 
(list 2485.415 111.5314) 
(list 2559.4375 112.1814)))
(apply 'command (append '("pline") coords '("c")))
(setq currobj (ssadd (entlast) currobj))
(setq coords (list 
(list 2559.4375 112.0384) 
(list 2485.415 111.3884) 
(list 2485.415 111.2114) 
(list 2559.4375 111.9614)))
(apply 'command (append '("pline") coords '("c")))
(setq currobj (ssadd (entlast) currobj))
(command "_layer" "set" "nitride" "")
(command "_layer" "set" "text" "")
(command "_circle" "2559.0625,100.8184" "0.075")
(command "_circle" "2559.0625,101.1184" "0.075")
(command "_circle" "2559.0625,101.4184" "0.075")
(command "_circle" "2559.0625,101.7184" "0.075")
(command "_circle" "2559.0625,102.0184" "0.075")
(command "_circle" "2558.7625,100.8184" "0.075")
(command "_circle" "2558.7625,101.1184" "0.075")
(command "_circle" "2558.7625,101.4184" "0.075")
(command "_circle" "2558.7625,101.7184" "0.075")
(command "_circle" "2558.7625,102.0184" "0.075")
(command "_circle" "2558.4625,100.8184" "0.075")
(command "_circle" "2558.4625,101.1184" "0.075")
(command "_circle" "2558.4625,101.4184" "0.075")
(command "_circle" "2558.4625,101.7184" "0.075")
(command "_circle" "2558.4625,102.0184" "0.075")
(command "_circle" "2558.1625,100.8184" "0.075")
(command "_circle" "2558.1625,101.1184" "0.075")
(command "_circle" "2558.1625,101.4184" "0.075")
(command "_circle" "2558.1625,101.7184" "0.075")
(command "_circle" "2558.1625,102.0184" "0.075")
(command "_circle" "2557.8625,100.8184" "0.075")
(command "_circle" "2557.8625,101.1184" "0.075")
(command "_circle" "2557.8625,101.4184" "0.075")
(command "_circle" "2557.8625,101.7184" "0.075")
(command "_circle" "2557.8625,102.0184" "0.075")
(command "_layer" "set" "nitride" "")
(setq coords (list 
(list 2560.2625 126.2614) 
(list 2560.2625 241.9061) 
(list 2559.7375 241.9061) 
(list 2559.7375 126.2614)))
(apply 'command (append '("pline") coords '("c")))
(setq currobj (ssadd (entlast) currobj))
(command "_layer" "set" "prebias" "")
(command "_rectangle" "2559.7375,126.2614" "2560.2625,241.9061")
(setq currobj (ssadd (entlast) currobj))
(command "_layer" "set" "nitride" "")
(setq coords (list 
(list 2560.2625 241.9061) 
(list 2560.5625 251.9061) 
(list 2560.5625 251.9061) 
(list 2560.5625 252.9061) 
(list 2634.585 252.1561) 
(list 2634.585 257.0991) 
(list 2560.5625 256.3491) 
(list 2560.5625 257.3491) 
(list 2560.5625 257.3491) 
(list 2560.2625 267.3491) 
(list 2559.7375 267.3491) 
(list 2559.4375 257.3491) 
(list 2559.4375 257.3491) 
(list 2559.4375 256.3491) 
(list 2485.415 257.0991) 
(list 2485.415 252.1561) 
(list 2559.4375 252.9061) 
(list 2559.4375 251.9061) 
(list 2559.4375 251.9061) 
(list 2559.7375 241.9061)))
(apply 'command (append '("pline") coords '("c")))
(setq currobj (ssadd (entlast) currobj))
(command "_layer" "set" "prebias" "")
(setq coords (list 
(list 2559.4375 241.9061) 
(list 2559.4375 252.9061) 
(list 2485.415 252.1561) 
(list 2485.415 257.0991) 
(list 2559.4375 256.3491) 
(list 2559.4375 267.3491) 
(list 2560.5625 267.3491) 
(list 2560.5625 256.3491) 
(list 2634.585 257.0991) 
(list 2634.585 252.1561) 
(list 2560.5625 252.9061) 
(list 2560.5625 241.9061)))
(apply 'command (append '("pline") coords '("c")))
(setq currobj (ssadd (entlast) currobj))
(command "_layer" "set" "nitride" "")
(command "_layer" "set" "fda1" "")
(setq coords (list 
(list 2560.5625 253.0491) 
(list 2634.585 252.2991) 
(list 2634.585 252.4761) 
(list 2560.5625 253.1261)))
(apply 'command (append '("pline") coords '("c")))
(setq currobj (ssadd (entlast) currobj))
(setq coords (list 
(list 2560.5625 253.2691) 
(list 2634.585 252.6191) 
(list 2634.585 252.7961) 
(list 2560.5625 253.3461)))
(apply 'command (append '("pline") coords '("c")))
(setq currobj (ssadd (entlast) currobj))
(setq coords (list 
(list 2560.5625 253.4891) 
(list 2634.585 252.9391) 
(list 2634.585 253.1161) 
(list 2560.5625 253.5661)))
(apply 'command (append '("pline") coords '("c")))
(setq currobj (ssadd (entlast) currobj))
(setq coords (list 
(list 2560.5625 253.7091) 
(list 2634.585 253.2591) 
(list 2634.585 253.4361) 
(list 2560.5625 253.7861)))
(apply 'command (append '("pline") coords '("c")))
(setq currobj (ssadd (entlast) currobj))
(setq coords (list 
(list 2560.5625 253.9291) 
(list 2634.585 253.5791) 
(list 2634.585 253.7561) 
(list 2560.5625 254.0061)))
(apply 'command (append '("pline") coords '("c")))
(setq currobj (ssadd (entlast) currobj))
(setq coords (list 
(list 2560.5625 254.1491) 
(list 2634.585 253.8991) 
(list 2634.585 254.0761) 
(list 2560.5625 254.2261)))
(apply 'command (append '("pline") coords '("c")))
(setq currobj (ssadd (entlast) currobj))
(setq coords (list 
(list 2560.5625 254.3691) 
(list 2634.585 254.2191) 
(list 2634.585 254.3961) 
(list 2560.5625 254.4461)))
(apply 'command (append '("pline") coords '("c")))
(setq currobj (ssadd (entlast) currobj))
(setq coords (list 
(list 2560.5625 254.5891) 
(list 2634.585 254.5391) 
(list 2634.585 254.7161) 
(list 2560.5625 254.6661)))
(apply 'command (append '("pline") coords '("c")))
(setq currobj (ssadd (entlast) currobj))
(setq coords (list 
(list 2560.5625 254.8091) 
(list 2634.585 254.8591) 
(list 2634.585 255.0361) 
(list 2560.5625 254.8861)))
(apply 'command (append '("pline") coords '("c")))
(setq currobj (ssadd (entlast) currobj))
(setq coords (list 
(list 2560.5625 255.0291) 
(list 2634.585 255.1791) 
(list 2634.585 255.3561) 
(list 2560.5625 255.1061)))
(apply 'command (append '("pline") coords '("c")))
(setq currobj (ssadd (entlast) currobj))
(setq coords (list 
(list 2560.5625 255.2491) 
(list 2634.585 255.4991) 
(list 2634.585 255.6761) 
(list 2560.5625 255.3261)))
(apply 'command (append '("pline") coords '("c")))
(setq currobj (ssadd (entlast) currobj))
(setq coords (list 
(list 2560.5625 255.4691) 
(list 2634.585 255.8191) 
(list 2634.585 255.9961) 
(list 2560.5625 255.5461)))
(apply 'command (append '("pline") coords '("c")))
(setq currobj (ssadd (entlast) currobj))
(setq coords (list 
(list 2560.5625 255.6891) 
(list 2634.585 256.1391) 
(list 2634.585 256.3161) 
(list 2560.5625 255.7661)))
(apply 'command (append '("pline") coords '("c")))
(setq currobj (ssadd (entlast) currobj))
(setq coords (list 
(list 2560.5625 255.9091) 
(list 2634.585 256.4591) 
(list 2634.585 256.6361) 
(list 2560.5625 255.9861)))
(apply 'command (append '("pline") coords '("c")))
(setq currobj (ssadd (entlast) currobj))
(setq coords (list 
(list 2560.5625 256.1291) 
(list 2634.585 256.7791) 
(list 2634.585 256.9561) 
(list 2560.5625 256.2061)))
(apply 'command (append '("pline") coords '("c")))
(setq currobj (ssadd (entlast) currobj))
(setq coords (list 
(list 2559.4375 256.2061) 
(list 2485.415 256.9561) 
(list 2485.415 256.7791) 
(list 2559.4375 256.1291)))
(apply 'command (append '("pline") coords '("c")))
(setq currobj (ssadd (entlast) currobj))
(setq coords (list 
(list 2559.4375 255.9861) 
(list 2485.415 256.6361) 
(list 2485.415 256.4591) 
(list 2559.4375 255.9091)))
(apply 'command (append '("pline") coords '("c")))
(setq currobj (ssadd (entlast) currobj))
(setq coords (list 
(list 2559.4375 255.7661) 
(list 2485.415 256.3161) 
(list 2485.415 256.1391) 
(list 2559.4375 255.6891)))
(apply 'command (append '("pline") coords '("c")))
(setq currobj (ssadd (entlast) currobj))
(setq coords (list 
(list 2559.4375 255.5461) 
(list 2485.415 255.9961) 
(list 2485.415 255.8191) 
(list 2559.4375 255.4691)))
(apply 'command (append '("pline") coords '("c")))
(setq currobj (ssadd (entlast) currobj))
(setq coords (list 
(list 2559.4375 255.3261) 
(list 2485.415 255.6761) 
(list 2485.415 255.4991) 
(list 2559.4375 255.2491)))
(apply 'command (append '("pline") coords '("c")))
(setq currobj (ssadd (entlast) currobj))
(setq coords (list 
(list 2559.4375 255.1061) 
(list 2485.415 255.3561) 
(list 2485.415 255.1791) 
(list 2559.4375 255.0291)))
(apply 'command (append '("pline") coords '("c")))
(setq currobj (ssadd (entlast) currobj))
(setq coords (list 
(list 2559.4375 254.8861) 
(list 2485.415 255.0361) 
(list 2485.415 254.8591) 
(list 2559.4375 254.8091)))
(apply 'command (append '("pline") coords '("c")))
(setq currobj (ssadd (entlast) currobj))
(setq coords (list 
(list 2559.4375 254.6661) 
(list 2485.415 254.7161) 
(list 2485.415 254.5391) 
(list 2559.4375 254.5891)))
(apply 'command (append '("pline") coords '("c")))
(setq currobj (ssadd (entlast) currobj))
(setq coords (list 
(list 2559.4375 254.4461) 
(list 2485.415 254.3961) 
(list 2485.415 254.2191) 
(list 2559.4375 254.3691)))
(apply 'command (append '("pline") coords '("c")))
(setq currobj (ssadd (entlast) currobj))
(setq coords (list 
(list 2559.4375 254.2261) 
(list 2485.415 254.0761) 
(list 2485.415 253.8991) 
(list 2559.4375 254.1491)))
(apply 'command (append '("pline") coords '("c")))
(setq currobj (ssadd (entlast) currobj))
(setq coords (list 
(list 2559.4375 254.0061) 
(list 2485.415 253.7561) 
(list 2485.415 253.5791) 
(list 2559.4375 253.9291)))
(apply 'command (append '("pline") coords '("c")))
(setq currobj (ssadd (entlast) currobj))
(setq coords (list 
(list 2559.4375 253.7861) 
(list 2485.415 253.4361) 
(list 2485.415 253.2591) 
(list 2559.4375 253.7091)))
(apply 'command (append '("pline") coords '("c")))
(setq currobj (ssadd (entlast) currobj))
(setq coords (list 
(list 2559.4375 253.5661) 
(list 2485.415 253.1161) 
(list 2485.415 252.9391) 
(list 2559.4375 253.4891)))
(apply 'command (append '("pline") coords '("c")))
(setq currobj (ssadd (entlast) currobj))
(setq coords (list 
(list 2559.4375 253.3461) 
(list 2485.415 252.7961) 
(list 2485.415 252.6191) 
(list 2559.4375 253.2691)))
(apply 'command (append '("pline") coords '("c")))
(setq currobj (ssadd (entlast) currobj))
(setq coords (list 
(list 2559.4375 253.1261) 
(list 2485.415 252.4761) 
(list 2485.415 252.2991) 
(list 2559.4375 253.0491)))
(apply 'command (append '("pline") coords '("c")))
(setq currobj (ssadd (entlast) currobj))
(command "_layer" "set" "nitride" "")
(command "_layer" "set" "text" "")
(command "_circle" "2559.0625,241.9061" "0.075")
(command "_circle" "2559.0625,242.2061" "0.075")
(command "_circle" "2559.0625,242.5061" "0.075")
(command "_circle" "2559.0625,242.8061" "0.075")
(command "_circle" "2559.0625,243.1061" "0.075")
(command "_circle" "2558.7625,241.9061" "0.075")
(command "_circle" "2558.7625,242.2061" "0.075")
(command "_circle" "2558.7625,242.5061" "0.075")
(command "_circle" "2558.7625,242.8061" "0.075")
(command "_circle" "2558.7625,243.1061" "0.075")
(command "_circle" "2558.4625,241.9061" "0.075")
(command "_circle" "2558.4625,242.2061" "0.075")
(command "_circle" "2558.4625,242.5061" "0.075")
(command "_circle" "2558.4625,242.8061" "0.075")
(command "_circle" "2558.4625,243.1061" "0.075")
(command "_circle" "2558.1625,241.9061" "0.075")
(command "_circle" "2558.1625,242.2061" "0.075")
(command "_circle" "2558.1625,242.5061" "0.075")
(command "_circle" "2558.1625,242.8061" "0.075")
(command "_circle" "2558.1625,243.1061" "0.075")
(command "_circle" "2557.8625,241.9061" "0.075")
(command "_circle" "2557.8625,242.2061" "0.075")
(command "_circle" "2557.8625,242.5061" "0.075")
(command "_circle" "2557.8625,242.8061" "0.075")
(command "_circle" "2557.8625,243.1061" "0.075")
(command "_layer" "set" "nitride" "")
(setq coords (list 
(list 2560.2625 267.3491) 
(list 2560.2625 382.9939) 
(list 2559.7375 382.9939) 
(list 2559.7375 267.3491)))
(apply 'command (append '("pline") coords '("c")))
(setq currobj (ssadd (entlast) currobj))
(command "_layer" "set" "prebias" "")
(command "_rectangle" "2559.7375,267.3491" "2560.2625,382.9939")
(setq currobj (ssadd (entlast) currobj))
(command "_layer" "set" "nitride" "")
(setq coords (list 
(list 2560.2625 382.9939) 
(list 2560.5625 392.9939) 
(list 2560.5625 392.9939) 
(list 2560.5625 393.9939) 
(list 2634.585 393.2439) 
(list 2634.585 398.1869) 
(list 2560.5625 397.4369) 
(list 2560.5625 398.4369) 
(list 2560.5625 398.4369) 
(list 2560.2625 408.4369) 
(list 2559.7375 408.4369) 
(list 2559.4375 398.4369) 
(list 2559.4375 398.4369) 
(list 2559.4375 397.4369) 
(list 2485.415 398.1869) 
(list 2485.415 393.2439) 
(list 2559.4375 393.9939) 
(list 2559.4375 392.9939) 
(list 2559.4375 392.9939) 
(list 2559.7375 382.9939)))
(apply 'command (append '("pline") coords '("c")))
(setq currobj (ssadd (entlast) currobj))
(command "_layer" "set" "prebias" "")
(setq coords (list 
(list 2559.4375 382.9939) 
(list 2559.4375 393.9939) 
(list 2485.415 393.2439) 
(list 2485.415 398.1869) 
(list 2559.4375 397.4369) 
(list 2559.4375 408.4369) 
(list 2560.5625 408.4369) 
(list 2560.5625 397.4369) 
(list 2634.585 398.1869) 
(list 2634.585 393.2439) 
(list 2560.5625 393.9939) 
(list 2560.5625 382.9939)))
(apply 'command (append '("pline") coords '("c")))
(setq currobj (ssadd (entlast) currobj))
(command "_layer" "set" "nitride" "")
(command "_layer" "set" "fda1" "")
(setq coords (list 
(list 2560.5625 394.1369) 
(list 2634.585 393.3869) 
(list 2634.585 393.5639) 
(list 2560.5625 394.2139)))
(apply 'command (append '("pline") coords '("c")))
(setq currobj (ssadd (entlast) currobj))
(setq coords (list 
(list 2560.5625 394.3569) 
(list 2634.585 393.7069) 
(list 2634.585 393.8839) 
(list 2560.5625 394.4339)))
(apply 'command (append '("pline") coords '("c")))
(setq currobj (ssadd (entlast) currobj))
(setq coords (list 
(list 2560.5625 394.5769) 
(list 2634.585 394.0269) 
(list 2634.585 394.2039) 
(list 2560.5625 394.6539)))
(apply 'command (append '("pline") coords '("c")))
(setq currobj (ssadd (entlast) currobj))
(setq coords (list 
(list 2560.5625 394.7969) 
(list 2634.585 394.3469) 
(list 2634.585 394.5239) 
(list 2560.5625 394.8739)))
(apply 'command (append '("pline") coords '("c")))
(setq currobj (ssadd (entlast) currobj))
(setq coords (list 
(list 2560.5625 395.0169) 
(list 2634.585 394.6669) 
(list 2634.585 394.8439) 
(list 2560.5625 395.0939)))
(apply 'command (append '("pline") coords '("c")))
(setq currobj (ssadd (entlast) currobj))
(setq coords (list 
(list 2560.5625 395.2369) 
(list 2634.585 394.9869) 
(list 2634.585 395.1639) 
(list 2560.5625 395.3139)))
(apply 'command (append '("pline") coords '("c")))
(setq currobj (ssadd (entlast) currobj))
(setq coords (list 
(list 2560.5625 395.4569) 
(list 2634.585 395.3069) 
(list 2634.585 395.4839) 
(list 2560.5625 395.5339)))
(apply 'command (append '("pline") coords '("c")))
(setq currobj (ssadd (entlast) currobj))
(setq coords (list 
(list 2560.5625 395.6769) 
(list 2634.585 395.6269) 
(list 2634.585 395.8039) 
(list 2560.5625 395.7539)))
(apply 'command (append '("pline") coords '("c")))
(setq currobj (ssadd (entlast) currobj))
(setq coords (list 
(list 2560.5625 395.8969) 
(list 2634.585 395.9469) 
(list 2634.585 396.1239) 
(list 2560.5625 395.9739)))
(apply 'command (append '("pline") coords '("c")))
(setq currobj (ssadd (entlast) currobj))
(setq coords (list 
(list 2560.5625 396.1169) 
(list 2634.585 396.2669) 
(list 2634.585 396.4439) 
(list 2560.5625 396.1939)))
(apply 'command (append '("pline") coords '("c")))
(setq currobj (ssadd (entlast) currobj))
(setq coords (list 
(list 2560.5625 396.3369) 
(list 2634.585 396.5869) 
(list 2634.585 396.7639) 
(list 2560.5625 396.4139)))
(apply 'command (append '("pline") coords '("c")))
(setq currobj (ssadd (entlast) currobj))
(setq coords (list 
(list 2560.5625 396.5569) 
(list 2634.585 396.9069) 
(list 2634.585 397.0839) 
(list 2560.5625 396.6339)))
(apply 'command (append '("pline") coords '("c")))
(setq currobj (ssadd (entlast) currobj))
(setq coords (list 
(list 2560.5625 396.7769) 
(list 2634.585 397.2269) 
(list 2634.585 397.4039) 
(list 2560.5625 396.8539)))
(apply 'command (append '("pline") coords '("c")))
(setq currobj (ssadd (entlast) currobj))
(setq coords (list 
(list 2560.5625 396.9969) 
(list 2634.585 397.5469) 
(list 2634.585 397.7239) 
(list 2560.5625 397.0739)))
(apply 'command (append '("pline") coords '("c")))
(setq currobj (ssadd (entlast) currobj))
(setq coords (list 
(list 2560.5625 397.2169) 
(list 2634.585 397.8669) 
(list 2634.585 398.0439) 
(list 2560.5625 397.2939)))
(apply 'command (append '("pline") coords '("c")))
(setq currobj (ssadd (entlast) currobj))
(setq coords (list 
(list 2559.4375 397.2939) 
(list 2485.415 398.0439) 
(list 2485.415 397.8669) 
(list 2559.4375 397.2169)))
(apply 'command (append '("pline") coords '("c")))
(setq currobj (ssadd (entlast) currobj))
(setq coords (list 
(list 2559.4375 397.0739) 
(list 2485.415 397.7239) 
(list 2485.415 397.5469) 
(list 2559.4375 396.9969)))
(apply 'command (append '("pline") coords '("c")))
(setq currobj (ssadd (entlast) currobj))
(setq coords (list 
(list 2559.4375 396.8539) 
(list 2485.415 397.4039) 
(list 2485.415 397.2269) 
(list 2559.4375 396.7769)))
(apply 'command (append '("pline") coords '("c")))
(setq currobj (ssadd (entlast) currobj))
(setq coords (list 
(list 2559.4375 396.6339) 
(list 2485.415 397.0839) 
(list 2485.415 396.9069) 
(list 2559.4375 396.5569)))
(apply 'command (append '("pline") coords '("c")))
(setq currobj (ssadd (entlast) currobj))
(setq coords (list 
(list 2559.4375 396.4139) 
(list 2485.415 396.7639) 
(list 2485.415 396.5869) 
(list 2559.4375 396.3369)))
(apply 'command (append '("pline") coords '("c")))
(setq currobj (ssadd (entlast) currobj))
(setq coords (list 
(list 2559.4375 396.1939) 
(list 2485.415 396.4439) 
(list 2485.415 396.2669) 
(list 2559.4375 396.1169)))
(apply 'command (append '("pline") coords '("c")))
(setq currobj (ssadd (entlast) currobj))
(setq coords (list 
(list 2559.4375 395.9739) 
(list 2485.415 396.1239) 
(list 2485.415 395.9469) 
(list 2559.4375 395.8969)))
(apply 'command (append '("pline") coords '("c")))
(setq currobj (ssadd (entlast) currobj))
(setq coords (list 
(list 2559.4375 395.7539) 
(list 2485.415 395.8039) 
(list 2485.415 395.6269) 
(list 2559.4375 395.6769)))
(apply 'command (append '("pline") coords '("c")))
(setq currobj (ssadd (entlast) currobj))
(setq coords (list 
(list 2559.4375 395.5339) 
(list 2485.415 395.4839) 
(list 2485.415 395.3069) 
(list 2559.4375 395.4569)))
(apply 'command (append '("pline") coords '("c")))
(setq currobj (ssadd (entlast) currobj))
(setq coords (list 
(list 2559.4375 395.3139) 
(list 2485.415 395.1639) 
(list 2485.415 394.9869) 
(list 2559.4375 395.2369)))
(apply 'command (append '("pline") coords '("c")))
(setq currobj (ssadd (entlast) currobj))
(setq coords (list 
(list 2559.4375 395.0939) 
(list 2485.415 394.8439) 
(list 2485.415 394.6669) 
(list 2559.4375 395.0169)))
(apply 'command (append '("pline") coords '("c")))
(setq currobj (ssadd (entlast) currobj))
(setq coords (list 
(list 2559.4375 394.8739) 
(list 2485.415 394.5239) 
(list 2485.415 394.3469) 
(list 2559.4375 394.7969)))
(apply 'command (append '("pline") coords '("c")))
(setq currobj (ssadd (entlast) currobj))
(setq coords (list 
(list 2559.4375 394.6539) 
(list 2485.415 394.2039) 
(list 2485.415 394.0269) 
(list 2559.4375 394.5769)))
(apply 'command (append '("pline") coords '("c")))
(setq currobj (ssadd (entlast) currobj))
(setq coords (list 
(list 2559.4375 394.4339) 
(list 2485.415 393.8839) 
(list 2485.415 393.7069) 
(list 2559.4375 394.3569)))
(apply 'command (append '("pline") coords '("c")))
(setq currobj (ssadd (entlast) currobj))
(setq coords (list 
(list 2559.4375 394.2139) 
(list 2485.415 393.5639) 
(list 2485.415 393.3869) 
(list 2559.4375 394.1369)))
(apply 'command (append '("pline") coords '("c")))
(setq currobj (ssadd (entlast) currobj))
(command "_layer" "set" "nitride" "")
(command "_layer" "set" "text" "")
(command "_circle" "2559.0625,382.9939" "0.075")
(command "_circle" "2559.0625,383.2939" "0.075")
(command "_circle" "2559.0625,383.5939" "0.075")
(command "_circle" "2559.0625,383.8939" "0.075")
(command "_circle" "2559.0625,384.1939" "0.075")
(command "_circle" "2558.7625,382.9939" "0.075")
(command "_circle" "2558.7625,383.2939" "0.075")
(command "_circle" "2558.7625,383.5939" "0.075")
(command "_circle" "2558.7625,383.8939" "0.075")
(command "_circle" "2558.7625,384.1939" "0.075")
(command "_circle" "2558.4625,382.9939" "0.075")
(command "_circle" "2558.4625,383.2939" "0.075")
(command "_circle" "2558.4625,383.5939" "0.075")
(command "_circle" "2558.4625,383.8939" "0.075")
(command "_circle" "2558.4625,384.1939" "0.075")
(command "_circle" "2558.1625,382.9939" "0.075")
(command "_circle" "2558.1625,383.2939" "0.075")
(command "_circle" "2558.1625,383.5939" "0.075")
(command "_circle" "2558.1625,383.8939" "0.075")
(command "_circle" "2558.1625,384.1939" "0.075")
(command "_circle" "2557.8625,382.9939" "0.075")
(command "_circle" "2557.8625,383.2939" "0.075")
(command "_circle" "2557.8625,383.5939" "0.075")
(command "_circle" "2557.8625,383.8939" "0.075")
(command "_circle" "2557.8625,384.1939" "0.075")
(command "_layer" "set" "nitride" "")
(setq coords (list 
(list 2560.2625 408.4369) 
(list 2560.2625 524.0816) 
(list 2559.7375 524.0816) 
(list 2559.7375 408.4369)))
(apply 'command (append '("pline") coords '("c")))
(setq currobj (ssadd (entlast) currobj))
(command "_layer" "set" "prebias" "")
(command "_rectangle" "2559.7375,408.4369" "2560.2625,524.0816")
(setq currobj (ssadd (entlast) currobj))
(command "_layer" "set" "nitride" "")
(setq coords (list 
(list 2560.2625 524.0816) 
(list 2560.5625 534.0816) 
(list 2560.5625 534.0816) 
(list 2560.5625 535.0816) 
(list 2634.585 534.3316) 
(list 2634.585 539.2746) 
(list 2560.5625 538.5246) 
(list 2560.5625 539.5246) 
(list 2560.5625 539.5246) 
(list 2560.2625 549.5246) 
(list 2559.7375 549.5246) 
(list 2559.4375 539.5246) 
(list 2559.4375 539.5246) 
(list 2559.4375 538.5246) 
(list 2485.415 539.2746) 
(list 2485.415 534.3316) 
(list 2559.4375 535.0816) 
(list 2559.4375 534.0816) 
(list 2559.4375 534.0816) 
(list 2559.7375 524.0816)))
(apply 'command (append '("pline") coords '("c")))
(setq currobj (ssadd (entlast) currobj))
(command "_layer" "set" "prebias" "")
(setq coords (list 
(list 2559.4375 524.0816) 
(list 2559.4375 535.0816) 
(list 2485.415 534.3316) 
(list 2485.415 539.2746) 
(list 2559.4375 538.5246) 
(list 2559.4375 549.5246) 
(list 2560.5625 549.5246) 
(list 2560.5625 538.5246) 
(list 2634.585 539.2746) 
(list 2634.585 534.3316) 
(list 2560.5625 535.0816) 
(list 2560.5625 524.0816)))
(apply 'command (append '("pline") coords '("c")))
(setq currobj (ssadd (entlast) currobj))
(command "_layer" "set" "nitride" "")
(command "_layer" "set" "fda1" "")
(setq coords (list 
(list 2560.5625 535.2246) 
(list 2634.585 534.4746) 
(list 2634.585 534.6516) 
(list 2560.5625 535.3016)))
(apply 'command (append '("pline") coords '("c")))
(setq currobj (ssadd (entlast) currobj))
(setq coords (list 
(list 2560.5625 535.4446) 
(list 2634.585 534.7946) 
(list 2634.585 534.9716) 
(list 2560.5625 535.5216)))
(apply 'command (append '("pline") coords '("c")))
(setq currobj (ssadd (entlast) currobj))
(setq coords (list 
(list 2560.5625 535.6646) 
(list 2634.585 535.1146) 
(list 2634.585 535.2916) 
(list 2560.5625 535.7416)))
(apply 'command (append '("pline") coords '("c")))
(setq currobj (ssadd (entlast) currobj))
(setq coords (list 
(list 2560.5625 535.8846) 
(list 2634.585 535.4346) 
(list 2634.585 535.6116) 
(list 2560.5625 535.9616)))
(apply 'command (append '("pline") coords '("c")))
(setq currobj (ssadd (entlast) currobj))
(setq coords (list 
(list 2560.5625 536.1046) 
(list 2634.585 535.7546) 
(list 2634.585 535.9316) 
(list 2560.5625 536.1816)))
(apply 'command (append '("pline") coords '("c")))
(setq currobj (ssadd (entlast) currobj))
(setq coords (list 
(list 2560.5625 536.3246) 
(list 2634.585 536.0746) 
(list 2634.585 536.2516) 
(list 2560.5625 536.4016)))
(apply 'command (append '("pline") coords '("c")))
(setq currobj (ssadd (entlast) currobj))
(setq coords (list 
(list 2560.5625 536.5446) 
(list 2634.585 536.3946) 
(list 2634.585 536.5716) 
(list 2560.5625 536.6216)))
(apply 'command (append '("pline") coords '("c")))
(setq currobj (ssadd (entlast) currobj))
(setq coords (list 
(list 2560.5625 536.7646) 
(list 2634.585 536.7146) 
(list 2634.585 536.8916) 
(list 2560.5625 536.8416)))
(apply 'command (append '("pline") coords '("c")))
(setq currobj (ssadd (entlast) currobj))
(setq coords (list 
(list 2560.5625 536.9846) 
(list 2634.585 537.0346) 
(list 2634.585 537.2116) 
(list 2560.5625 537.0616)))
(apply 'command (append '("pline") coords '("c")))
(setq currobj (ssadd (entlast) currobj))
(setq coords (list 
(list 2560.5625 537.2046) 
(list 2634.585 537.3546) 
(list 2634.585 537.5316) 
(list 2560.5625 537.2816)))
(apply 'command (append '("pline") coords '("c")))
(setq currobj (ssadd (entlast) currobj))
(setq coords (list 
(list 2560.5625 537.4246) 
(list 2634.585 537.6746) 
(list 2634.585 537.8516) 
(list 2560.5625 537.5016)))
(apply 'command (append '("pline") coords '("c")))
(setq currobj (ssadd (entlast) currobj))
(setq coords (list 
(list 2560.5625 537.6446) 
(list 2634.585 537.9946) 
(list 2634.585 538.1716) 
(list 2560.5625 537.7216)))
(apply 'command (append '("pline") coords '("c")))
(setq currobj (ssadd (entlast) currobj))
(setq coords (list 
(list 2560.5625 537.8646) 
(list 2634.585 538.3146) 
(list 2634.585 538.4916) 
(list 2560.5625 537.9416)))
(apply 'command (append '("pline") coords '("c")))
(setq currobj (ssadd (entlast) currobj))
(setq coords (list 
(list 2560.5625 538.0846) 
(list 2634.585 538.6346) 
(list 2634.585 538.8116) 
(list 2560.5625 538.1616)))
(apply 'command (append '("pline") coords '("c")))
(setq currobj (ssadd (entlast) currobj))
(setq coords (list 
(list 2560.5625 538.3046) 
(list 2634.585 538.9546) 
(list 2634.585 539.1316) 
(list 2560.5625 538.3816)))
(apply 'command (append '("pline") coords '("c")))
(setq currobj (ssadd (entlast) currobj))
(setq coords (list 
(list 2559.4375 538.3816) 
(list 2485.415 539.1316) 
(list 2485.415 538.9546) 
(list 2559.4375 538.3046)))
(apply 'command (append '("pline") coords '("c")))
(setq currobj (ssadd (entlast) currobj))
(setq coords (list 
(list 2559.4375 538.1616) 
(list 2485.415 538.8116) 
(list 2485.415 538.6346) 
(list 2559.4375 538.0846)))
(apply 'command (append '("pline") coords '("c")))
(setq currobj (ssadd (entlast) currobj))
(setq coords (list 
(list 2559.4375 537.9416) 
(list 2485.415 538.4916) 
(list 2485.415 538.3146) 
(list 2559.4375 537.8646)))
(apply 'command (append '("pline") coords '("c")))
(setq currobj (ssadd (entlast) currobj))
(setq coords (list 
(list 2559.4375 537.7216) 
(list 2485.415 538.1716) 
(list 2485.415 537.9946) 
(list 2559.4375 537.6446)))
(apply 'command (append '("pline") coords '("c")))
(setq currobj (ssadd (entlast) currobj))
(setq coords (list 
(list 2559.4375 537.5016) 
(list 2485.415 537.8516) 
(list 2485.415 537.6746) 
(list 2559.4375 537.4246)))
(apply 'command (append '("pline") coords '("c")))
(setq currobj (ssadd (entlast) currobj))
(setq coords (list 
(list 2559.4375 537.2816) 
(list 2485.415 537.5316) 
(list 2485.415 537.3546) 
(list 2559.4375 537.2046)))
(apply 'command (append '("pline") coords '("c")))
(setq currobj (ssadd (entlast) currobj))
(setq coords (list 
(list 2559.4375 537.0616) 
(list 2485.415 537.2116) 
(list 2485.415 537.0346) 
(list 2559.4375 536.9846)))
(apply 'command (append '("pline") coords '("c")))
(setq currobj (ssadd (entlast) currobj))
(setq coords (list 
(list 2559.4375 536.8416) 
(list 2485.415 536.8916) 
(list 2485.415 536.7146) 
(list 2559.4375 536.7646)))
(apply 'command (append '("pline") coords '("c")))
(setq currobj (ssadd (entlast) currobj))
(setq coords (list 
(list 2559.4375 536.6216) 
(list 2485.415 536.5716) 
(list 2485.415 536.3946) 
(list 2559.4375 536.5446)))
(apply 'command (append '("pline") coords '("c")))
(setq currobj (ssadd (entlast) currobj))
(setq coords (list 
(list 2559.4375 536.4016) 
(list 2485.415 536.2516) 
(list 2485.415 536.0746) 
(list 2559.4375 536.3246)))
(apply 'command (append '("pline") coords '("c")))
(setq currobj (ssadd (entlast) currobj))
(setq coords (list 
(list 2559.4375 536.1816) 
(list 2485.415 535.9316) 
(list 2485.415 535.7546) 
(list 2559.4375 536.1046)))
(apply 'command (append '("pline") coords '("c")))
(setq currobj (ssadd (entlast) currobj))
(setq coords (list 
(list 2559.4375 535.9616) 
(list 2485.415 535.6116) 
(list 2485.415 535.4346) 
(list 2559.4375 535.8846)))
(apply 'command (append '("pline") coords '("c")))
(setq currobj (ssadd (entlast) currobj))
(setq coords (list 
(list 2559.4375 535.7416) 
(list 2485.415 535.2916) 
(list 2485.415 535.1146) 
(list 2559.4375 535.6646)))
(apply 'command (append '("pline") coords '("c")))
(setq currobj (ssadd (entlast) currobj))
(setq coords (list 
(list 2559.4375 535.5216) 
(list 2485.415 534.9716) 
(list 2485.415 534.7946) 
(list 2559.4375 535.4446)))
(apply 'command (append '("pline") coords '("c")))
(setq currobj (ssadd (entlast) currobj))
(setq coords (list 
(list 2559.4375 535.3016) 
(list 2485.415 534.6516) 
(list 2485.415 534.4746) 
(list 2559.4375 535.2246)))
(apply 'command (append '("pline") coords '("c")))
(setq currobj (ssadd (entlast) currobj))
(command "_layer" "set" "nitride" "")
(command "_layer" "set" "text" "")
(command "_circle" "2559.0625,524.0816" "0.075")
(command "_circle" "2559.0625,524.3816" "0.075")
(command "_circle" "2559.0625,524.6816" "0.075")
(command "_circle" "2559.0625,524.9816" "0.075")
(command "_circle" "2559.0625,525.2816" "0.075")
(command "_circle" "2558.7625,524.0816" "0.075")
(command "_circle" "2558.7625,524.3816" "0.075")
(command "_circle" "2558.7625,524.6816" "0.075")
(command "_circle" "2558.7625,524.9816" "0.075")
(command "_circle" "2558.7625,525.2816" "0.075")
(command "_circle" "2558.4625,524.0816" "0.075")
(command "_circle" "2558.4625,524.3816" "0.075")
(command "_circle" "2558.4625,524.6816" "0.075")
(command "_circle" "2558.4625,524.9816" "0.075")
(command "_circle" "2558.4625,525.2816" "0.075")
(command "_circle" "2558.1625,524.0816" "0.075")
(command "_circle" "2558.1625,524.3816" "0.075")
(command "_circle" "2558.1625,524.6816" "0.075")
(command "_circle" "2558.1625,524.9816" "0.075")
(command "_circle" "2558.1625,525.2816" "0.075")
(command "_circle" "2557.8625,524.0816" "0.075")
(command "_circle" "2557.8625,524.3816" "0.075")
(command "_circle" "2557.8625,524.6816" "0.075")
(command "_circle" "2557.8625,524.9816" "0.075")
(command "_circle" "2557.8625,525.2816" "0.075")
(command "_layer" "set" "nitride" "")
(setq coords (list 
(list 2560.2625 549.5246) 
(list 2560.2625 665.1693) 
(list 2559.7375 665.1693) 
(list 2559.7375 549.5246)))
(apply 'command (append '("pline") coords '("c")))
(setq currobj (ssadd (entlast) currobj))
(command "_layer" "set" "prebias" "")
(command "_rectangle" "2559.7375,549.5246" "2560.2625,665.1693")
(setq currobj (ssadd (entlast) currobj))
(command "_layer" "set" "nitride" "")
(setq coords (list 
(list 2560.2625 665.1693) 
(list 2560.5625 675.1693) 
(list 2560.5625 675.1693) 
(list 2560.5625 676.1693) 
(list 2634.585 675.4193) 
(list 2634.585 680.3623) 
(list 2560.5625 679.6123) 
(list 2560.5625 680.6123) 
(list 2560.5625 680.6123) 
(list 2560.2625 690.6123) 
(list 2559.7375 690.6123) 
(list 2559.4375 680.6123) 
(list 2559.4375 680.6123) 
(list 2559.4375 679.6123) 
(list 2485.415 680.3623) 
(list 2485.415 675.4193) 
(list 2559.4375 676.1693) 
(list 2559.4375 675.1693) 
(list 2559.4375 675.1693) 
(list 2559.7375 665.1693)))
(apply 'command (append '("pline") coords '("c")))
(setq currobj (ssadd (entlast) currobj))
(command "_layer" "set" "prebias" "")
(setq coords (list 
(list 2559.4375 665.1693) 
(list 2559.4375 676.1693) 
(list 2485.415 675.4193) 
(list 2485.415 680.3623) 
(list 2559.4375 679.6123) 
(list 2559.4375 690.6123) 
(list 2560.5625 690.6123) 
(list 2560.5625 679.6123) 
(list 2634.585 680.3623) 
(list 2634.585 675.4193) 
(list 2560.5625 676.1693) 
(list 2560.5625 665.1693)))
(apply 'command (append '("pline") coords '("c")))
(setq currobj (ssadd (entlast) currobj))
(command "_layer" "set" "nitride" "")
(command "_layer" "set" "fda1" "")
(setq coords (list 
(list 2560.5625 676.3123) 
(list 2634.585 675.5623) 
(list 2634.585 675.7393) 
(list 2560.5625 676.3893)))
(apply 'command (append '("pline") coords '("c")))
(setq currobj (ssadd (entlast) currobj))
(setq coords (list 
(list 2560.5625 676.5323) 
(list 2634.585 675.8823) 
(list 2634.585 676.0593) 
(list 2560.5625 676.6093)))
(apply 'command (append '("pline") coords '("c")))
(setq currobj (ssadd (entlast) currobj))
(setq coords (list 
(list 2560.5625 676.7523) 
(list 2634.585 676.2023) 
(list 2634.585 676.3793) 
(list 2560.5625 676.8293)))
(apply 'command (append '("pline") coords '("c")))
(setq currobj (ssadd (entlast) currobj))
(setq coords (list 
(list 2560.5625 676.9723) 
(list 2634.585 676.5223) 
(list 2634.585 676.6993) 
(list 2560.5625 677.0493)))
(apply 'command (append '("pline") coords '("c")))
(setq currobj (ssadd (entlast) currobj))
(setq coords (list 
(list 2560.5625 677.1923) 
(list 2634.585 676.8423) 
(list 2634.585 677.0193) 
(list 2560.5625 677.2693)))
(apply 'command (append '("pline") coords '("c")))
(setq currobj (ssadd (entlast) currobj))
(setq coords (list 
(list 2560.5625 677.4123) 
(list 2634.585 677.1623) 
(list 2634.585 677.3393) 
(list 2560.5625 677.4893)))
(apply 'command (append '("pline") coords '("c")))
(setq currobj (ssadd (entlast) currobj))
(setq coords (list 
(list 2560.5625 677.6323) 
(list 2634.585 677.4823) 
(list 2634.585 677.6593) 
(list 2560.5625 677.7093)))
(apply 'command (append '("pline") coords '("c")))
(setq currobj (ssadd (entlast) currobj))
(setq coords (list 
(list 2560.5625 677.8523) 
(list 2634.585 677.8023) 
(list 2634.585 677.9793) 
(list 2560.5625 677.9293)))
(apply 'command (append '("pline") coords '("c")))
(setq currobj (ssadd (entlast) currobj))
(setq coords (list 
(list 2560.5625 678.0723) 
(list 2634.585 678.1223) 
(list 2634.585 678.2993) 
(list 2560.5625 678.1493)))
(apply 'command (append '("pline") coords '("c")))
(setq currobj (ssadd (entlast) currobj))
(setq coords (list 
(list 2560.5625 678.2923) 
(list 2634.585 678.4423) 
(list 2634.585 678.6193) 
(list 2560.5625 678.3693)))
(apply 'command (append '("pline") coords '("c")))
(setq currobj (ssadd (entlast) currobj))
(setq coords (list 
(list 2560.5625 678.5123) 
(list 2634.585 678.7623) 
(list 2634.585 678.9393) 
(list 2560.5625 678.5893)))
(apply 'command (append '("pline") coords '("c")))
(setq currobj (ssadd (entlast) currobj))
(setq coords (list 
(list 2560.5625 678.7323) 
(list 2634.585 679.0823) 
(list 2634.585 679.2593) 
(list 2560.5625 678.8093)))
(apply 'command (append '("pline") coords '("c")))
(setq currobj (ssadd (entlast) currobj))
(setq coords (list 
(list 2560.5625 678.9523) 
(list 2634.585 679.4023) 
(list 2634.585 679.5793) 
(list 2560.5625 679.0293)))
(apply 'command (append '("pline") coords '("c")))
(setq currobj (ssadd (entlast) currobj))
(setq coords (list 
(list 2560.5625 679.1723) 
(list 2634.585 679.7223) 
(list 2634.585 679.8993) 
(list 2560.5625 679.2493)))
(apply 'command (append '("pline") coords '("c")))
(setq currobj (ssadd (entlast) currobj))
(setq coords (list 
(list 2560.5625 679.3923) 
(list 2634.585 680.0423) 
(list 2634.585 680.2193) 
(list 2560.5625 679.4693)))
(apply 'command (append '("pline") coords '("c")))
(setq currobj (ssadd (entlast) currobj))
(setq coords (list 
(list 2559.4375 679.4693) 
(list 2485.415 680.2193) 
(list 2485.415 680.0423) 
(list 2559.4375 679.3923)))
(apply 'command (append '("pline") coords '("c")))
(setq currobj (ssadd (entlast) currobj))
(setq coords (list 
(list 2559.4375 679.2493) 
(list 2485.415 679.8993) 
(list 2485.415 679.7223) 
(list 2559.4375 679.1723)))
(apply 'command (append '("pline") coords '("c")))
(setq currobj (ssadd (entlast) currobj))
(setq coords (list 
(list 2559.4375 679.0293) 
(list 2485.415 679.5793) 
(list 2485.415 679.4023) 
(list 2559.4375 678.9523)))
(apply 'command (append '("pline") coords '("c")))
(setq currobj (ssadd (entlast) currobj))
(setq coords (list 
(list 2559.4375 678.8093) 
(list 2485.415 679.2593) 
(list 2485.415 679.0823) 
(list 2559.4375 678.7323)))
(apply 'command (append '("pline") coords '("c")))
(setq currobj (ssadd (entlast) currobj))
(setq coords (list 
(list 2559.4375 678.5893) 
(list 2485.415 678.9393) 
(list 2485.415 678.7623) 
(list 2559.4375 678.5123)))
(apply 'command (append '("pline") coords '("c")))
(setq currobj (ssadd (entlast) currobj))
(setq coords (list 
(list 2559.4375 678.3693) 
(list 2485.415 678.6193) 
(list 2485.415 678.4423) 
(list 2559.4375 678.2923)))
(apply 'command (append '("pline") coords '("c")))
(setq currobj (ssadd (entlast) currobj))
(setq coords (list 
(list 2559.4375 678.1493) 
(list 2485.415 678.2993) 
(list 2485.415 678.1223) 
(list 2559.4375 678.0723)))
(apply 'command (append '("pline") coords '("c")))
(setq currobj (ssadd (entlast) currobj))
(setq coords (list 
(list 2559.4375 677.9293) 
(list 2485.415 677.9793) 
(list 2485.415 677.8023) 
(list 2559.4375 677.8523)))
(apply 'command (append '("pline") coords '("c")))
(setq currobj (ssadd (entlast) currobj))
(setq coords (list 
(list 2559.4375 677.7093) 
(list 2485.415 677.6593) 
(list 2485.415 677.4823) 
(list 2559.4375 677.6323)))
(apply 'command (append '("pline") coords '("c")))
(setq currobj (ssadd (entlast) currobj))
(setq coords (list 
(list 2559.4375 677.4893) 
(list 2485.415 677.3393) 
(list 2485.415 677.1623) 
(list 2559.4375 677.4123)))
(apply 'command (append '("pline") coords '("c")))
(setq currobj (ssadd (entlast) currobj))
(setq coords (list 
(list 2559.4375 677.2693) 
(list 2485.415 677.0193) 
(list 2485.415 676.8423) 
(list 2559.4375 677.1923)))
(apply 'command (append '("pline") coords '("c")))
(setq currobj (ssadd (entlast) currobj))
(setq coords (list 
(list 2559.4375 677.0493) 
(list 2485.415 676.6993) 
(list 2485.415 676.5223) 
(list 2559.4375 676.9723)))
(apply 'command (append '("pline") coords '("c")))
(setq currobj (ssadd (entlast) currobj))
(setq coords (list 
(list 2559.4375 676.8293) 
(list 2485.415 676.3793) 
(list 2485.415 676.2023) 
(list 2559.4375 676.7523)))
(apply 'command (append '("pline") coords '("c")))
(setq currobj (ssadd (entlast) currobj))
(setq coords (list 
(list 2559.4375 676.6093) 
(list 2485.415 676.0593) 
(list 2485.415 675.8823) 
(list 2559.4375 676.5323)))
(apply 'command (append '("pline") coords '("c")))
(setq currobj (ssadd (entlast) currobj))
(setq coords (list 
(list 2559.4375 676.3893) 
(list 2485.415 675.7393) 
(list 2485.415 675.5623) 
(list 2559.4375 676.3123)))
(apply 'command (append '("pline") coords '("c")))
(setq currobj (ssadd (entlast) currobj))
(command "_layer" "set" "nitride" "")
(command "_layer" "set" "text" "")
(command "_circle" "2559.0625,665.1693" "0.075")
(command "_circle" "2559.0625,665.4693" "0.075")
(command "_circle" "2559.0625,665.7693" "0.075")
(command "_circle" "2559.0625,666.0693" "0.075")
(command "_circle" "2559.0625,666.3693" "0.075")
(command "_circle" "2558.7625,665.1693" "0.075")
(command "_circle" "2558.7625,665.4693" "0.075")
(command "_circle" "2558.7625,665.7693" "0.075")
(command "_circle" "2558.7625,666.0693" "0.075")
(command "_circle" "2558.7625,666.3693" "0.075")
(command "_circle" "2558.4625,665.1693" "0.075")
(command "_circle" "2558.4625,665.4693" "0.075")
(command "_circle" "2558.4625,665.7693" "0.075")
(command "_circle" "2558.4625,666.0693" "0.075")
(command "_circle" "2558.4625,666.3693" "0.075")
(command "_circle" "2558.1625,665.1693" "0.075")
(command "_circle" "2558.1625,665.4693" "0.075")
(command "_circle" "2558.1625,665.7693" "0.075")
(command "_circle" "2558.1625,666.0693" "0.075")
(command "_circle" "2558.1625,666.3693" "0.075")
(command "_circle" "2557.8625,665.1693" "0.075")
(command "_circle" "2557.8625,665.4693" "0.075")
(command "_circle" "2557.8625,665.7693" "0.075")
(command "_circle" "2557.8625,666.0693" "0.075")
(command "_circle" "2557.8625,666.3693" "0.075")
(command "_layer" "set" "nitride" "")
(setq coords (list 
(list 2560.2625 690.6123) 
(list 2560.2625 806.257) 
(list 2559.7375 806.257) 
(list 2559.7375 690.6123)))
(apply 'command (append '("pline") coords '("c")))
(setq currobj (ssadd (entlast) currobj))
(command "_layer" "set" "prebias" "")
(command "_rectangle" "2559.7375,690.6123" "2560.2625,806.257")
(setq currobj (ssadd (entlast) currobj))
(command "_layer" "set" "nitride" "")
(setq coords (list 
(list 2560.2625 806.257) 
(list 2560.5625 816.257) 
(list 2560.5625 816.257) 
(list 2560.5625 817.257) 
(list 2634.585 816.507) 
(list 2634.585 821.45) 
(list 2560.5625 820.7) 
(list 2560.5625 821.7) 
(list 2560.5625 821.7) 
(list 2560.2625 831.7) 
(list 2559.7375 831.7) 
(list 2559.4375 821.7) 
(list 2559.4375 821.7) 
(list 2559.4375 820.7) 
(list 2485.415 821.45) 
(list 2485.415 816.507) 
(list 2559.4375 817.257) 
(list 2559.4375 816.257) 
(list 2559.4375 816.257) 
(list 2559.7375 806.257)))
(apply 'command (append '("pline") coords '("c")))
(setq currobj (ssadd (entlast) currobj))
(command "_layer" "set" "prebias" "")
(setq coords (list 
(list 2559.4375 806.257) 
(list 2559.4375 817.257) 
(list 2485.415 816.507) 
(list 2485.415 821.45) 
(list 2559.4375 820.7) 
(list 2559.4375 831.7) 
(list 2560.5625 831.7) 
(list 2560.5625 820.7) 
(list 2634.585 821.45) 
(list 2634.585 816.507) 
(list 2560.5625 817.257) 
(list 2560.5625 806.257)))
(apply 'command (append '("pline") coords '("c")))
(setq currobj (ssadd (entlast) currobj))
(command "_layer" "set" "nitride" "")
(command "_layer" "set" "fda1" "")
(setq coords (list 
(list 2560.5625 817.4) 
(list 2634.585 816.65) 
(list 2634.585 816.827) 
(list 2560.5625 817.477)))
(apply 'command (append '("pline") coords '("c")))
(setq currobj (ssadd (entlast) currobj))
(setq coords (list 
(list 2560.5625 817.62) 
(list 2634.585 816.97) 
(list 2634.585 817.147) 
(list 2560.5625 817.697)))
(apply 'command (append '("pline") coords '("c")))
(setq currobj (ssadd (entlast) currobj))
(setq coords (list 
(list 2560.5625 817.84) 
(list 2634.585 817.29) 
(list 2634.585 817.467) 
(list 2560.5625 817.917)))
(apply 'command (append '("pline") coords '("c")))
(setq currobj (ssadd (entlast) currobj))
(setq coords (list 
(list 2560.5625 818.06) 
(list 2634.585 817.61) 
(list 2634.585 817.787) 
(list 2560.5625 818.137)))
(apply 'command (append '("pline") coords '("c")))
(setq currobj (ssadd (entlast) currobj))
(setq coords (list 
(list 2560.5625 818.28) 
(list 2634.585 817.93) 
(list 2634.585 818.107) 
(list 2560.5625 818.357)))
(apply 'command (append '("pline") coords '("c")))
(setq currobj (ssadd (entlast) currobj))
(setq coords (list 
(list 2560.5625 818.5) 
(list 2634.585 818.25) 
(list 2634.585 818.427) 
(list 2560.5625 818.577)))
(apply 'command (append '("pline") coords '("c")))
(setq currobj (ssadd (entlast) currobj))
(setq coords (list 
(list 2560.5625 818.72) 
(list 2634.585 818.57) 
(list 2634.585 818.747) 
(list 2560.5625 818.797)))
(apply 'command (append '("pline") coords '("c")))
(setq currobj (ssadd (entlast) currobj))
(setq coords (list 
(list 2560.5625 818.94) 
(list 2634.585 818.89) 
(list 2634.585 819.067) 
(list 2560.5625 819.017)))
(apply 'command (append '("pline") coords '("c")))
(setq currobj (ssadd (entlast) currobj))
(setq coords (list 
(list 2560.5625 819.16) 
(list 2634.585 819.21) 
(list 2634.585 819.387) 
(list 2560.5625 819.237)))
(apply 'command (append '("pline") coords '("c")))
(setq currobj (ssadd (entlast) currobj))
(setq coords (list 
(list 2560.5625 819.38) 
(list 2634.585 819.53) 
(list 2634.585 819.707) 
(list 2560.5625 819.457)))
(apply 'command (append '("pline") coords '("c")))
(setq currobj (ssadd (entlast) currobj))
(setq coords (list 
(list 2560.5625 819.6) 
(list 2634.585 819.85) 
(list 2634.585 820.027) 
(list 2560.5625 819.677)))
(apply 'command (append '("pline") coords '("c")))
(setq currobj (ssadd (entlast) currobj))
(setq coords (list 
(list 2560.5625 819.82) 
(list 2634.585 820.17) 
(list 2634.585 820.347) 
(list 2560.5625 819.897)))
(apply 'command (append '("pline") coords '("c")))
(setq currobj (ssadd (entlast) currobj))
(setq coords (list 
(list 2560.5625 820.04) 
(list 2634.585 820.49) 
(list 2634.585 820.667) 
(list 2560.5625 820.117)))
(apply 'command (append '("pline") coords '("c")))
(setq currobj (ssadd (entlast) currobj))
(setq coords (list 
(list 2560.5625 820.26) 
(list 2634.585 820.81) 
(list 2634.585 820.987) 
(list 2560.5625 820.337)))
(apply 'command (append '("pline") coords '("c")))
(setq currobj (ssadd (entlast) currobj))
(setq coords (list 
(list 2560.5625 820.48) 
(list 2634.585 821.13) 
(list 2634.585 821.307) 
(list 2560.5625 820.557)))
(apply 'command (append '("pline") coords '("c")))
(setq currobj (ssadd (entlast) currobj))
(setq coords (list 
(list 2559.4375 820.557) 
(list 2485.415 821.307) 
(list 2485.415 821.13) 
(list 2559.4375 820.48)))
(apply 'command (append '("pline") coords '("c")))
(setq currobj (ssadd (entlast) currobj))
(setq coords (list 
(list 2559.4375 820.337) 
(list 2485.415 820.987) 
(list 2485.415 820.81) 
(list 2559.4375 820.26)))
(apply 'command (append '("pline") coords '("c")))
(setq currobj (ssadd (entlast) currobj))
(setq coords (list 
(list 2559.4375 820.117) 
(list 2485.415 820.667) 
(list 2485.415 820.49) 
(list 2559.4375 820.04)))
(apply 'command (append '("pline") coords '("c")))
(setq currobj (ssadd (entlast) currobj))
(setq coords (list 
(list 2559.4375 819.897) 
(list 2485.415 820.347) 
(list 2485.415 820.17) 
(list 2559.4375 819.82)))
(apply 'command (append '("pline") coords '("c")))
(setq currobj (ssadd (entlast) currobj))
(setq coords (list 
(list 2559.4375 819.677) 
(list 2485.415 820.027) 
(list 2485.415 819.85) 
(list 2559.4375 819.6)))
(apply 'command (append '("pline") coords '("c")))
(setq currobj (ssadd (entlast) currobj))
(setq coords (list 
(list 2559.4375 819.457) 
(list 2485.415 819.707) 
(list 2485.415 819.53) 
(list 2559.4375 819.38)))
(apply 'command (append '("pline") coords '("c")))
(setq currobj (ssadd (entlast) currobj))
(setq coords (list 
(list 2559.4375 819.237) 
(list 2485.415 819.387) 
(list 2485.415 819.21) 
(list 2559.4375 819.16)))
(apply 'command (append '("pline") coords '("c")))
(setq currobj (ssadd (entlast) currobj))
(setq coords (list 
(list 2559.4375 819.017) 
(list 2485.415 819.067) 
(list 2485.415 818.89) 
(list 2559.4375 818.94)))
(apply 'command (append '("pline") coords '("c")))
(setq currobj (ssadd (entlast) currobj))
(setq coords (list 
(list 2559.4375 818.797) 
(list 2485.415 818.747) 
(list 2485.415 818.57) 
(list 2559.4375 818.72)))
(apply 'command (append '("pline") coords '("c")))
(setq currobj (ssadd (entlast) currobj))
(setq coords (list 
(list 2559.4375 818.577) 
(list 2485.415 818.427) 
(list 2485.415 818.25) 
(list 2559.4375 818.5)))
(apply 'command (append '("pline") coords '("c")))
(setq currobj (ssadd (entlast) currobj))
(setq coords (list 
(list 2559.4375 818.357) 
(list 2485.415 818.107) 
(list 2485.415 817.93) 
(list 2559.4375 818.28)))
(apply 'command (append '("pline") coords '("c")))
(setq currobj (ssadd (entlast) currobj))
(setq coords (list 
(list 2559.4375 818.137) 
(list 2485.415 817.787) 
(list 2485.415 817.61) 
(list 2559.4375 818.06)))
(apply 'command (append '("pline") coords '("c")))
(setq currobj (ssadd (entlast) currobj))
(setq coords (list 
(list 2559.4375 817.917) 
(list 2485.415 817.467) 
(list 2485.415 817.29) 
(list 2559.4375 817.84)))
(apply 'command (append '("pline") coords '("c")))
(setq currobj (ssadd (entlast) currobj))
(setq coords (list 
(list 2559.4375 817.697) 
(list 2485.415 817.147) 
(list 2485.415 816.97) 
(list 2559.4375 817.62)))
(apply 'command (append '("pline") coords '("c")))
(setq currobj (ssadd (entlast) currobj))
(setq coords (list 
(list 2559.4375 817.477) 
(list 2485.415 816.827) 
(list 2485.415 816.65) 
(list 2559.4375 817.4)))
(apply 'command (append '("pline") coords '("c")))
(setq currobj (ssadd (entlast) currobj))
(command "_layer" "set" "nitride" "")
(command "_layer" "set" "text" "")
(command "_circle" "2559.0625,806.257" "0.075")
(command "_circle" "2559.0625,806.557" "0.075")
(command "_circle" "2559.0625,806.857" "0.075")
(command "_circle" "2559.0625,807.157" "0.075")
(command "_circle" "2559.0625,807.457" "0.075")
(command "_circle" "2558.7625,806.257" "0.075")
(command "_circle" "2558.7625,806.557" "0.075")
(command "_circle" "2558.7625,806.857" "0.075")
(command "_circle" "2558.7625,807.157" "0.075")
(command "_circle" "2558.7625,807.457" "0.075")
(command "_circle" "2558.4625,806.257" "0.075")
(command "_circle" "2558.4625,806.557" "0.075")
(command "_circle" "2558.4625,806.857" "0.075")
(command "_circle" "2558.4625,807.157" "0.075")
(command "_circle" "2558.4625,807.457" "0.075")
(command "_circle" "2558.1625,806.257" "0.075")
(command "_circle" "2558.1625,806.557" "0.075")
(command "_circle" "2558.1625,806.857" "0.075")
(command "_circle" "2558.1625,807.157" "0.075")
(command "_circle" "2558.1625,807.457" "0.075")
(command "_circle" "2557.8625,806.257" "0.075")
(command "_circle" "2557.8625,806.557" "0.075")
(command "_circle" "2557.8625,806.857" "0.075")
(command "_circle" "2557.8625,807.157" "0.075")
(command "_circle" "2557.8625,807.457" "0.075")
(command "_layer" "set" "nitride" "")
(setq coords (list 
(list 2560.2625 831.7) 
(list 2560.2625 836.7) 
(list 2559.7375 836.7) 
(list 2559.7375 831.7)))
(apply 'command (append '("pline") coords '("c")))
(setq currobj (ssadd (entlast) currobj))
(command "_layer" "set" "prebias" "")
(command "_rectangle" "2559.7375,831.7" "2560.2625,836.7")
(setq currobj (ssadd (entlast) currobj))
(command "_layer" "set" "nitride" "")
(setq cooledsinglenanobeam8 currobj)
(setq currobj nil)
(setq currobj (ssadd))
; DRAWING PHOTONIC CRYSTAL
(command "_layer" "set" "negYjunc" "")
(setq coords (list 
(list 2560.125 866.7) 
(list 2560 851.7) 
(list 2560 866.7)))
(apply 'command (append '("pline") coords '("c")))
(setq currobj (ssadd (entlast) currobj))
(setq coords (list 
(list 2560.2625 836.7) 
(list 2560.405 866.7) 
(list 2561.122 866.7) 
(list 2561.122 836.7)))
(apply 'command (append '("pline") coords '("c")))
(setq currobj (ssadd (entlast) currobj))
(setq coords (list 
(list 2559.875 866.7) 
(list 2560 851.7) 
(list 2560 866.7)))
(apply 'command (append '("pline") coords '("c")))
(setq currobj (ssadd (entlast) currobj))
(setq coords (list 
(list 2559.7375 836.7) 
(list 2559.595 866.7) 
(list 2558.878 866.7) 
(list 2558.878 836.7)))
(apply 'command (append '("pline") coords '("c")))
(setq currobj (ssadd (entlast) currobj))
(command "_layer" "set" "nitride" "")
(setq yjunction8 currobj)
(setq currobj nil)
(setq currobj (ssadd))
(setq tap8 nil)
(setq tap8 (ssadd))
(command "_layer" "set" "phc" "")
(setq coords (list 
(list 2560 866.7) 
(list 2560.125 866.7) 
(list 2560.125 866.7103) 
(list 2560.125 866.7206) 
(list 2560.125 866.7308) 
(list 2560.125 866.7411) 
(list 2560.125 866.7514) 
(list 2560.125 866.7617) 
(list 2560.125 866.7719) 
(list 2560.125 866.7822) 
(list 2560.125 866.7925) 
(list 2560.125 866.8028) 
(list 2560.125 866.8131) 
(list 2560.125 866.8233) 
(list 2560.125 866.8336) 
(list 2560.125 866.8439) 
(list 2560.125 866.8542) 
(list 2560.125 866.8644) 
(list 2560.125 866.8747) 
(list 2560.125 866.885) 
(list 2560.125 866.8953) 
(list 2560.125 866.9056) 
(list 2560.125 866.9158) 
(list 2560.125 866.9261) 
(list 2560.125 866.9364) 
(list 2560.125 866.9467) 
(list 2560.125 866.9569) 
(list 2560.125 866.9672) 
(list 2560.125 866.9775) 
(list 2560.125 866.9878) 
(list 2560.125 866.9981) 
(list 2560.125 867.0083) 
(list 2560.125 867.0186) 
(list 2560.125 867.0289) 
(list 2560.125 867.0392) 
(list 2560.125 867.0494) 
(list 2560.125 867.0597) 
(list 2560.125 867.07) 
(list 2560 867.07)))
(apply 'command (append '("pline") coords '("c")))
(setq tap8 (ssadd (entlast) tap8))
(command "_mirror" (entlast) "" "2560,900" "2560,901" "No")
(setq tap8 (ssadd (entlast) tap8))
(setq coords (list 
(list 2560.4154 866.7) 
(list 2560.405 866.7) 
(list 2560.4053 866.7103) 
(list 2560.4055 866.7206) 
(list 2560.4058 866.7308) 
(list 2560.4059 866.7411) 
(list 2560.406 866.7514) 
(list 2560.4059 866.7617) 
(list 2560.4058 866.7719) 
(list 2560.4056 866.7822) 
(list 2560.4052 866.7925) 
(list 2560.4048 866.8028) 
(list 2560.4043 866.8131) 
(list 2560.4037 866.8233) 
(list 2560.4031 866.8336) 
(list 2560.4025 866.8439) 
(list 2560.402 866.8542) 
(list 2560.4015 866.8644) 
(list 2560.401 866.8747) 
(list 2560.4007 866.885) 
(list 2560.4006 866.8953) 
(list 2560.4006 866.9056) 
(list 2560.4008 866.9158) 
(list 2560.4011 866.9261) 
(list 2560.4017 866.9364) 
(list 2560.4025 866.9467) 
(list 2560.4034 866.9569) 
(list 2560.4045 866.9672) 
(list 2560.4057 866.9775) 
(list 2560.407 866.9878) 
(list 2560.4084 866.9981) 
(list 2560.4097 867.0083) 
(list 2560.411 867.0186) 
(list 2560.4123 867.0289) 
(list 2560.4134 867.0392) 
(list 2560.4143 867.0494) 
(list 2560.415 867.0597) 
(list 2560.4154 867.07) 
(list 2560.4154 867.07)))
(apply 'command (append '("pline") coords '("c")))
(setq tap8 (ssadd (entlast) tap8))
(command "_mirror" (entlast) "" "2560,900" "2560,901" "No")
(setq tap8 (ssadd (entlast) tap8))
(setq coords (list 
(list 2561.122 866.7) 
(list 2560.4154 866.7) 
(list 2560.4154 866.7103) 
(list 2560.4154 866.7206) 
(list 2560.4154 866.7308) 
(list 2560.4154 866.7411) 
(list 2560.4154 866.7514) 
(list 2560.4154 866.7617) 
(list 2560.4154 866.7719) 
(list 2560.4154 866.7822) 
(list 2560.4154 866.7925) 
(list 2560.4154 866.8028) 
(list 2560.4154 866.8131) 
(list 2560.4154 866.8233) 
(list 2560.4154 866.8336) 
(list 2560.4154 866.8439) 
(list 2560.4154 866.8542) 
(list 2560.4154 866.8644) 
(list 2560.4154 866.8747) 
(list 2560.4154 866.885) 
(list 2560.4154 866.8953) 
(list 2560.4154 866.9056) 
(list 2560.4154 866.9158) 
(list 2560.4154 866.9261) 
(list 2560.4154 866.9364) 
(list 2560.4154 866.9467) 
(list 2560.4154 866.9569) 
(list 2560.4154 866.9672) 
(list 2560.4154 866.9775) 
(list 2560.4154 866.9878) 
(list 2560.4154 866.9981) 
(list 2560.4154 867.0083) 
(list 2560.4154 867.0186) 
(list 2560.4154 867.0289) 
(list 2560.4154 867.0392) 
(list 2560.4154 867.0494) 
(list 2560.4154 867.0597) 
(list 2560.4154 867.07) 
(list 2561.122 867.07)))
(apply 'command (append '("pline") coords '("c")))
(setq tap8 (ssadd (entlast) tap8))
(command "_mirror" (entlast) "" "2560,900" "2560,901" "No")
(setq tap8 (ssadd (entlast) tap8))
(setq coords (list 
(list 2560 867.07) 
(list 2560.125 867.07) 
(list 2560.125 867.0803) 
(list 2560.125 867.0906) 
(list 2560.125 867.1008) 
(list 2560.125 867.1111) 
(list 2560.125 867.1214) 
(list 2560.125 867.1317) 
(list 2560.125 867.1419) 
(list 2560.125 867.1522) 
(list 2560.125 867.1625) 
(list 2560.125 867.1728) 
(list 2560.125 867.1831) 
(list 2560.125 867.1933) 
(list 2560.125 867.2036) 
(list 2560.125 867.2139) 
(list 2560.125 867.2242) 
(list 2560.125 867.2344) 
(list 2560.125 867.2447) 
(list 2560.125 867.255) 
(list 2560.125 867.2653) 
(list 2560.125 867.2756) 
(list 2560.125 867.2858) 
(list 2560.125 867.2961) 
(list 2560.125 867.3064) 
(list 2560.125 867.3167) 
(list 2560.125 867.3269) 
(list 2560.125 867.3372) 
(list 2560.125 867.3475) 
(list 2560.125 867.3578) 
(list 2560.125 867.3681) 
(list 2560.125 867.3783) 
(list 2560.125 867.3886) 
(list 2560.125 867.3989) 
(list 2560.125 867.4092) 
(list 2560.125 867.4194) 
(list 2560.125 867.4297) 
(list 2560.125 867.44) 
(list 2560 867.44)))
(apply 'command (append '("pline") coords '("c")))
(setq tap8 (ssadd (entlast) tap8))
(command "_mirror" (entlast) "" "2560,900" "2560,901" "No")
(setq tap8 (ssadd (entlast) tap8))
(setq coords (list 
(list 2560.4258 867.07) 
(list 2560.4154 867.07) 
(list 2560.4155 867.0803) 
(list 2560.4154 867.0906) 
(list 2560.4149 867.1008) 
(list 2560.4141 867.1111) 
(list 2560.413 867.1214) 
(list 2560.4116 867.1317) 
(list 2560.41 867.1419) 
(list 2560.4082 867.1522) 
(list 2560.4062 867.1625) 
(list 2560.4041 867.1728) 
(list 2560.402 867.1831) 
(list 2560.3999 867.1933) 
(list 2560.398 867.2036) 
(list 2560.3962 867.2139) 
(list 2560.3947 867.2242) 
(list 2560.3935 867.2344) 
(list 2560.3926 867.2447) 
(list 2560.3922 867.255) 
(list 2560.3922 867.2653) 
(list 2560.3926 867.2756) 
(list 2560.3935 867.2858) 
(list 2560.3948 867.2961) 
(list 2560.3966 867.3064) 
(list 2560.3987 867.3167) 
(list 2560.4011 867.3269) 
(list 2560.4038 867.3372) 
(list 2560.4066 867.3475) 
(list 2560.4096 867.3578) 
(list 2560.4125 867.3681) 
(list 2560.4154 867.3783) 
(list 2560.4181 867.3886) 
(list 2560.4205 867.3989) 
(list 2560.4225 867.4092) 
(list 2560.4241 867.4194) 
(list 2560.4252 867.4297) 
(list 2560.4258 867.44) 
(list 2560.4258 867.44)))
(apply 'command (append '("pline") coords '("c")))
(setq tap8 (ssadd (entlast) tap8))
(command "_mirror" (entlast) "" "2560,900" "2560,901" "No")
(setq tap8 (ssadd (entlast) tap8))
(setq coords (list 
(list 2561.122 867.07) 
(list 2560.4258 867.07) 
(list 2560.4258 867.0803) 
(list 2560.4258 867.0906) 
(list 2560.4258 867.1008) 
(list 2560.4258 867.1111) 
(list 2560.4258 867.1214) 
(list 2560.4258 867.1317) 
(list 2560.4258 867.1419) 
(list 2560.4258 867.1522) 
(list 2560.4258 867.1625) 
(list 2560.4258 867.1728) 
(list 2560.4258 867.1831) 
(list 2560.4258 867.1933) 
(list 2560.4258 867.2036) 
(list 2560.4258 867.2139) 
(list 2560.4258 867.2242) 
(list 2560.4258 867.2344) 
(list 2560.4258 867.2447) 
(list 2560.4258 867.255) 
(list 2560.4258 867.2653) 
(list 2560.4258 867.2756) 
(list 2560.4258 867.2858) 
(list 2560.4258 867.2961) 
(list 2560.4258 867.3064) 
(list 2560.4258 867.3167) 
(list 2560.4258 867.3269) 
(list 2560.4258 867.3372) 
(list 2560.4258 867.3475) 
(list 2560.4258 867.3578) 
(list 2560.4258 867.3681) 
(list 2560.4258 867.3783) 
(list 2560.4258 867.3886) 
(list 2560.4258 867.3989) 
(list 2560.4258 867.4092) 
(list 2560.4258 867.4194) 
(list 2560.4258 867.4297) 
(list 2560.4258 867.44) 
(list 2561.122 867.44)))
(apply 'command (append '("pline") coords '("c")))
(setq tap8 (ssadd (entlast) tap8))
(command "_mirror" (entlast) "" "2560,900" "2560,901" "No")
(setq tap8 (ssadd (entlast) tap8))
(setq coords (list 
(list 2560 867.44) 
(list 2560.125 867.44) 
(list 2560.125 867.4503) 
(list 2560.125 867.4606) 
(list 2560.125 867.4708) 
(list 2560.125 867.4811) 
(list 2560.125 867.4914) 
(list 2560.125 867.5017) 
(list 2560.125 867.5119) 
(list 2560.125 867.5222) 
(list 2560.125 867.5325) 
(list 2560.125 867.5428) 
(list 2560.125 867.5531) 
(list 2560.125 867.5633) 
(list 2560.125 867.5736) 
(list 2560.125 867.5839) 
(list 2560.125 867.5942) 
(list 2560.125 867.6044) 
(list 2560.125 867.6147) 
(list 2560.125 867.625) 
(list 2560.125 867.6353) 
(list 2560.125 867.6456) 
(list 2560.125 867.6558) 
(list 2560.125 867.6661) 
(list 2560.125 867.6764) 
(list 2560.125 867.6867) 
(list 2560.125 867.6969) 
(list 2560.125 867.7072) 
(list 2560.125 867.7175) 
(list 2560.125 867.7278) 
(list 2560.125 867.7381) 
(list 2560.125 867.7483) 
(list 2560.125 867.7586) 
(list 2560.125 867.7689) 
(list 2560.125 867.7792) 
(list 2560.125 867.7894) 
(list 2560.125 867.7997) 
(list 2560.125 867.81) 
(list 2560 867.81)))
(apply 'command (append '("pline") coords '("c")))
(setq tap8 (ssadd (entlast) tap8))
(command "_mirror" (entlast) "" "2560,900" "2560,901" "No")
(setq tap8 (ssadd (entlast) tap8))
(setq coords (list 
(list 2560.4362 867.44) 
(list 2560.4258 867.44) 
(list 2560.4258 867.4503) 
(list 2560.4252 867.4606) 
(list 2560.424 867.4708) 
(list 2560.4223 867.4811) 
(list 2560.42 867.4914) 
(list 2560.4173 867.5017) 
(list 2560.4142 867.5119) 
(list 2560.4107 867.5222) 
(list 2560.4071 867.5325) 
(list 2560.4034 867.5428) 
(list 2560.3997 867.5531) 
(list 2560.3961 867.5633) 
(list 2560.3928 867.5736) 
(list 2560.3899 867.5839) 
(list 2560.3874 867.5942) 
(list 2560.3855 867.6044) 
(list 2560.3843 867.6147) 
(list 2560.3837 867.625) 
(list 2560.3838 867.6353) 
(list 2560.3847 867.6456) 
(list 2560.3862 867.6558) 
(list 2560.3885 867.6661) 
(list 2560.3914 867.6764) 
(list 2560.3949 867.6867) 
(list 2560.3988 867.6969) 
(list 2560.4031 867.7072) 
(list 2560.4076 867.7175) 
(list 2560.4122 867.7278) 
(list 2560.4167 867.7381) 
(list 2560.4211 867.7483) 
(list 2560.4251 867.7586) 
(list 2560.4286 867.7689) 
(list 2560.4316 867.7792) 
(list 2560.4339 867.7894) 
(list 2560.4355 867.7997) 
(list 2560.4362 867.81) 
(list 2560.4362 867.81)))
(apply 'command (append '("pline") coords '("c")))
(setq tap8 (ssadd (entlast) tap8))
(command "_mirror" (entlast) "" "2560,900" "2560,901" "No")
(setq tap8 (ssadd (entlast) tap8))
(setq coords (list 
(list 2561.122 867.44) 
(list 2560.4362 867.44) 
(list 2560.4362 867.4503) 
(list 2560.4362 867.4606) 
(list 2560.4362 867.4708) 
(list 2560.4362 867.4811) 
(list 2560.4362 867.4914) 
(list 2560.4362 867.5017) 
(list 2560.4362 867.5119) 
(list 2560.4362 867.5222) 
(list 2560.4362 867.5325) 
(list 2560.4362 867.5428) 
(list 2560.4362 867.5531) 
(list 2560.4362 867.5633) 
(list 2560.4362 867.5736) 
(list 2560.4362 867.5839) 
(list 2560.4362 867.5942) 
(list 2560.4362 867.6044) 
(list 2560.4362 867.6147) 
(list 2560.4362 867.625) 
(list 2560.4362 867.6353) 
(list 2560.4362 867.6456) 
(list 2560.4362 867.6558) 
(list 2560.4362 867.6661) 
(list 2560.4362 867.6764) 
(list 2560.4362 867.6867) 
(list 2560.4362 867.6969) 
(list 2560.4362 867.7072) 
(list 2560.4362 867.7175) 
(list 2560.4362 867.7278) 
(list 2560.4362 867.7381) 
(list 2560.4362 867.7483) 
(list 2560.4362 867.7586) 
(list 2560.4362 867.7689) 
(list 2560.4362 867.7792) 
(list 2560.4362 867.7894) 
(list 2560.4362 867.7997) 
(list 2560.4362 867.81) 
(list 2561.122 867.81)))
(apply 'command (append '("pline") coords '("c")))
(setq tap8 (ssadd (entlast) tap8))
(command "_mirror" (entlast) "" "2560,900" "2560,901" "No")
(setq tap8 (ssadd (entlast) tap8))
(setq coords (list 
(list 2560 867.81) 
(list 2560.125 867.81) 
(list 2560.125 867.8203) 
(list 2560.125 867.8306) 
(list 2560.125 867.8408) 
(list 2560.125 867.8511) 
(list 2560.125 867.8614) 
(list 2560.125 867.8717) 
(list 2560.125 867.8819) 
(list 2560.125 867.8922) 
(list 2560.125 867.9025) 
(list 2560.125 867.9128) 
(list 2560.125 867.9231) 
(list 2560.125 867.9333) 
(list 2560.125 867.9436) 
(list 2560.125 867.9539) 
(list 2560.125 867.9642) 
(list 2560.125 867.9744) 
(list 2560.125 867.9847) 
(list 2560.125 867.995) 
(list 2560.125 868.0053) 
(list 2560.125 868.0156) 
(list 2560.125 868.0258) 
(list 2560.125 868.0361) 
(list 2560.125 868.0464) 
(list 2560.125 868.0567) 
(list 2560.125 868.0669) 
(list 2560.125 868.0772) 
(list 2560.125 868.0875) 
(list 2560.125 868.0978) 
(list 2560.125 868.1081) 
(list 2560.125 868.1183) 
(list 2560.125 868.1286) 
(list 2560.125 868.1389) 
(list 2560.125 868.1492) 
(list 2560.125 868.1594) 
(list 2560.125 868.1697) 
(list 2560.125 868.18) 
(list 2560 868.18)))
(apply 'command (append '("pline") coords '("c")))
(setq tap8 (ssadd (entlast) tap8))
(command "_mirror" (entlast) "" "2560,900" "2560,901" "No")
(setq tap8 (ssadd (entlast) tap8))
(setq coords (list 
(list 2560.4466 867.81) 
(list 2560.4362 867.81) 
(list 2560.4361 867.8203) 
(list 2560.435 867.8306) 
(list 2560.4332 867.8408) 
(list 2560.4305 867.8511) 
(list 2560.427 867.8614) 
(list 2560.4229 867.8717) 
(list 2560.4183 867.8819) 
(list 2560.4133 867.8922) 
(list 2560.408 867.9025) 
(list 2560.4027 867.9128) 
(list 2560.3974 867.9231) 
(list 2560.3923 867.9333) 
(list 2560.3877 867.9436) 
(list 2560.3836 867.9539) 
(list 2560.3802 867.9642) 
(list 2560.3776 867.9744) 
(list 2560.3759 867.9847) 
(list 2560.3751 867.995) 
(list 2560.3754 868.0053) 
(list 2560.3767 868.0156) 
(list 2560.379 868.0258) 
(list 2560.3822 868.0361) 
(list 2560.3863 868.0464) 
(list 2560.3911 868.0567) 
(list 2560.3965 868.0669) 
(list 2560.4024 868.0772) 
(list 2560.4085 868.0875) 
(list 2560.4147 868.0978) 
(list 2560.4209 868.1081) 
(list 2560.4267 868.1183) 
(list 2560.4321 868.1286) 
(list 2560.4368 868.1389) 
(list 2560.4408 868.1492) 
(list 2560.4438 868.1594) 
(list 2560.4457 868.1697) 
(list 2560.4466 868.18) 
(list 2560.4466 868.18)))
(apply 'command (append '("pline") coords '("c")))
(setq tap8 (ssadd (entlast) tap8))
(command "_mirror" (entlast) "" "2560,900" "2560,901" "No")
(setq tap8 (ssadd (entlast) tap8))
(setq coords (list 
(list 2561.122 867.81) 
(list 2560.4466 867.81) 
(list 2560.4466 867.8203) 
(list 2560.4466 867.8306) 
(list 2560.4466 867.8408) 
(list 2560.4466 867.8511) 
(list 2560.4466 867.8614) 
(list 2560.4466 867.8717) 
(list 2560.4466 867.8819) 
(list 2560.4466 867.8922) 
(list 2560.4466 867.9025) 
(list 2560.4466 867.9128) 
(list 2560.4466 867.9231) 
(list 2560.4466 867.9333) 
(list 2560.4466 867.9436) 
(list 2560.4466 867.9539) 
(list 2560.4466 867.9642) 
(list 2560.4466 867.9744) 
(list 2560.4466 867.9847) 
(list 2560.4466 867.995) 
(list 2560.4466 868.0053) 
(list 2560.4466 868.0156) 
(list 2560.4466 868.0258) 
(list 2560.4466 868.0361) 
(list 2560.4466 868.0464) 
(list 2560.4466 868.0567) 
(list 2560.4466 868.0669) 
(list 2560.4466 868.0772) 
(list 2560.4466 868.0875) 
(list 2560.4466 868.0978) 
(list 2560.4466 868.1081) 
(list 2560.4466 868.1183) 
(list 2560.4466 868.1286) 
(list 2560.4466 868.1389) 
(list 2560.4466 868.1492) 
(list 2560.4466 868.1594) 
(list 2560.4466 868.1697) 
(list 2560.4466 868.18) 
(list 2561.122 868.18)))
(apply 'command (append '("pline") coords '("c")))
(setq tap8 (ssadd (entlast) tap8))
(command "_mirror" (entlast) "" "2560,900" "2560,901" "No")
(setq tap8 (ssadd (entlast) tap8))
(setq coords (list 
(list 2560 868.18) 
(list 2560.125 868.18) 
(list 2560.125 868.1903) 
(list 2560.125 868.2006) 
(list 2560.125 868.2108) 
(list 2560.125 868.2211) 
(list 2560.125 868.2314) 
(list 2560.125 868.2417) 
(list 2560.125 868.2519) 
(list 2560.125 868.2622) 
(list 2560.125 868.2725) 
(list 2560.125 868.2828) 
(list 2560.125 868.2931) 
(list 2560.125 868.3033) 
(list 2560.125 868.3136) 
(list 2560.125 868.3239) 
(list 2560.125 868.3342) 
(list 2560.125 868.3444) 
(list 2560.125 868.3547) 
(list 2560.125 868.365) 
(list 2560.125 868.3753) 
(list 2560.125 868.3856) 
(list 2560.125 868.3958) 
(list 2560.125 868.4061) 
(list 2560.125 868.4164) 
(list 2560.125 868.4267) 
(list 2560.125 868.4369) 
(list 2560.125 868.4472) 
(list 2560.125 868.4575) 
(list 2560.125 868.4678) 
(list 2560.125 868.4781) 
(list 2560.125 868.4883) 
(list 2560.125 868.4986) 
(list 2560.125 868.5089) 
(list 2560.125 868.5192) 
(list 2560.125 868.5294) 
(list 2560.125 868.5397) 
(list 2560.125 868.55) 
(list 2560 868.55)))
(apply 'command (append '("pline") coords '("c")))
(setq tap8 (ssadd (entlast) tap8))
(command "_mirror" (entlast) "" "2560,900" "2560,901" "No")
(setq tap8 (ssadd (entlast) tap8))
(setq coords (list 
(list 2560.457 868.18) 
(list 2560.4466 868.18) 
(list 2560.4463 868.1903) 
(list 2560.4449 868.2006) 
(list 2560.4423 868.2108) 
(list 2560.4387 868.2211) 
(list 2560.434 868.2314) 
(list 2560.4286 868.2417) 
(list 2560.4225 868.2519) 
(list 2560.4159 868.2622) 
(list 2560.409 868.2725) 
(list 2560.402 868.2828) 
(list 2560.3951 868.2931) 
(list 2560.3885 868.3033) 
(list 2560.3825 868.3136) 
(list 2560.3773 868.3239) 
(list 2560.3729 868.3342) 
(list 2560.3696 868.3444) 
(list 2560.3675 868.3547) 
(list 2560.3666 868.365) 
(list 2560.367 868.3753) 
(list 2560.3687 868.3856) 
(list 2560.3717 868.3958) 
(list 2560.3759 868.4061) 
(list 2560.3811 868.4164) 
(list 2560.3873 868.4267) 
(list 2560.3942 868.4369) 
(list 2560.4016 868.4472) 
(list 2560.4094 868.4575) 
(list 2560.4173 868.4678) 
(list 2560.425 868.4781) 
(list 2560.4324 868.4883) 
(list 2560.4391 868.4986) 
(list 2560.445 868.5089) 
(list 2560.4499 868.5192) 
(list 2560.4536 868.5294) 
(list 2560.456 868.5397) 
(list 2560.457 868.55) 
(list 2560.457 868.55)))
(apply 'command (append '("pline") coords '("c")))
(setq tap8 (ssadd (entlast) tap8))
(command "_mirror" (entlast) "" "2560,900" "2560,901" "No")
(setq tap8 (ssadd (entlast) tap8))
(setq coords (list 
(list 2561.122 868.18) 
(list 2560.457 868.18) 
(list 2560.457 868.1903) 
(list 2560.457 868.2006) 
(list 2560.457 868.2108) 
(list 2560.457 868.2211) 
(list 2560.457 868.2314) 
(list 2560.457 868.2417) 
(list 2560.457 868.2519) 
(list 2560.457 868.2622) 
(list 2560.457 868.2725) 
(list 2560.457 868.2828) 
(list 2560.457 868.2931) 
(list 2560.457 868.3033) 
(list 2560.457 868.3136) 
(list 2560.457 868.3239) 
(list 2560.457 868.3342) 
(list 2560.457 868.3444) 
(list 2560.457 868.3547) 
(list 2560.457 868.365) 
(list 2560.457 868.3753) 
(list 2560.457 868.3856) 
(list 2560.457 868.3958) 
(list 2560.457 868.4061) 
(list 2560.457 868.4164) 
(list 2560.457 868.4267) 
(list 2560.457 868.4369) 
(list 2560.457 868.4472) 
(list 2560.457 868.4575) 
(list 2560.457 868.4678) 
(list 2560.457 868.4781) 
(list 2560.457 868.4883) 
(list 2560.457 868.4986) 
(list 2560.457 868.5089) 
(list 2560.457 868.5192) 
(list 2560.457 868.5294) 
(list 2560.457 868.5397) 
(list 2560.457 868.55) 
(list 2561.122 868.55)))
(apply 'command (append '("pline") coords '("c")))
(setq tap8 (ssadd (entlast) tap8))
(command "_mirror" (entlast) "" "2560,900" "2560,901" "No")
(setq tap8 (ssadd (entlast) tap8))
(setq coords (list 
(list 2560 868.55) 
(list 2560.125 868.55) 
(list 2560.125 868.5603) 
(list 2560.125 868.5706) 
(list 2560.125 868.5808) 
(list 2560.125 868.5911) 
(list 2560.125 868.6014) 
(list 2560.125 868.6117) 
(list 2560.125 868.6219) 
(list 2560.125 868.6322) 
(list 2560.125 868.6425) 
(list 2560.125 868.6528) 
(list 2560.125 868.6631) 
(list 2560.125 868.6733) 
(list 2560.125 868.6836) 
(list 2560.125 868.6939) 
(list 2560.125 868.7042) 
(list 2560.125 868.7144) 
(list 2560.125 868.7247) 
(list 2560.125 868.735) 
(list 2560.125 868.7453) 
(list 2560.125 868.7556) 
(list 2560.125 868.7658) 
(list 2560.125 868.7761) 
(list 2560.125 868.7864) 
(list 2560.125 868.7967) 
(list 2560.125 868.8069) 
(list 2560.125 868.8172) 
(list 2560.125 868.8275) 
(list 2560.125 868.8378) 
(list 2560.125 868.8481) 
(list 2560.125 868.8583) 
(list 2560.125 868.8686) 
(list 2560.125 868.8789) 
(list 2560.125 868.8892) 
(list 2560.125 868.8994) 
(list 2560.125 868.9097) 
(list 2560.125 868.92) 
(list 2560 868.92)))
(apply 'command (append '("pline") coords '("c")))
(setq tap8 (ssadd (entlast) tap8))
(command "_mirror" (entlast) "" "2560,900" "2560,901" "No")
(setq tap8 (ssadd (entlast) tap8))
(setq coords (list 
(list 2560.4674 868.55) 
(list 2560.457 868.55) 
(list 2560.4566 868.5603) 
(list 2560.4547 868.5706) 
(list 2560.4514 868.5808) 
(list 2560.4468 868.5911) 
(list 2560.4411 868.6014) 
(list 2560.4343 868.6117) 
(list 2560.4267 868.6219) 
(list 2560.4185 868.6322) 
(list 2560.4099 868.6425) 
(list 2560.4012 868.6528) 
(list 2560.3928 868.6631) 
(list 2560.3847 868.6733) 
(list 2560.3774 868.6836) 
(list 2560.3709 868.6939) 
(list 2560.3656 868.7042) 
(list 2560.3616 868.7144) 
(list 2560.3591 868.7247) 
(list 2560.3581 868.735) 
(list 2560.3586 868.7453) 
(list 2560.3608 868.7556) 
(list 2560.3644 868.7658) 
(list 2560.3695 868.7761) 
(list 2560.376 868.7864) 
(list 2560.3835 868.7967) 
(list 2560.3919 868.8069) 
(list 2560.4009 868.8172) 
(list 2560.4104 868.8275) 
(list 2560.4199 868.8378) 
(list 2560.4292 868.8481) 
(list 2560.4381 868.8583) 
(list 2560.4461 868.8686) 
(list 2560.4532 868.8789) 
(list 2560.459 868.8892) 
(list 2560.4634 868.8994) 
(list 2560.4663 868.9097) 
(list 2560.4674 868.92) 
(list 2560.4674 868.92)))
(apply 'command (append '("pline") coords '("c")))
(setq tap8 (ssadd (entlast) tap8))
(command "_mirror" (entlast) "" "2560,900" "2560,901" "No")
(setq tap8 (ssadd (entlast) tap8))
(setq coords (list 
(list 2561.122 868.55) 
(list 2560.4674 868.55) 
(list 2560.4674 868.5603) 
(list 2560.4674 868.5706) 
(list 2560.4674 868.5808) 
(list 2560.4674 868.5911) 
(list 2560.4674 868.6014) 
(list 2560.4674 868.6117) 
(list 2560.4674 868.6219) 
(list 2560.4674 868.6322) 
(list 2560.4674 868.6425) 
(list 2560.4674 868.6528) 
(list 2560.4674 868.6631) 
(list 2560.4674 868.6733) 
(list 2560.4674 868.6836) 
(list 2560.4674 868.6939) 
(list 2560.4674 868.7042) 
(list 2560.4674 868.7144) 
(list 2560.4674 868.7247) 
(list 2560.4674 868.735) 
(list 2560.4674 868.7453) 
(list 2560.4674 868.7556) 
(list 2560.4674 868.7658) 
(list 2560.4674 868.7761) 
(list 2560.4674 868.7864) 
(list 2560.4674 868.7967) 
(list 2560.4674 868.8069) 
(list 2560.4674 868.8172) 
(list 2560.4674 868.8275) 
(list 2560.4674 868.8378) 
(list 2560.4674 868.8481) 
(list 2560.4674 868.8583) 
(list 2560.4674 868.8686) 
(list 2560.4674 868.8789) 
(list 2560.4674 868.8892) 
(list 2560.4674 868.8994) 
(list 2560.4674 868.9097) 
(list 2560.4674 868.92) 
(list 2561.122 868.92)))
(apply 'command (append '("pline") coords '("c")))
(setq tap8 (ssadd (entlast) tap8))
(command "_mirror" (entlast) "" "2560,900" "2560,901" "No")
(setq tap8 (ssadd (entlast) tap8))
(setq coords (list 
(list 2560 868.92) 
(list 2560.125 868.92) 
(list 2560.125 868.9303) 
(list 2560.125 868.9406) 
(list 2560.125 868.9508) 
(list 2560.125 868.9611) 
(list 2560.125 868.9714) 
(list 2560.125 868.9817) 
(list 2560.125 868.9919) 
(list 2560.125 869.0022) 
(list 2560.125 869.0125) 
(list 2560.125 869.0228) 
(list 2560.125 869.0331) 
(list 2560.125 869.0433) 
(list 2560.125 869.0536) 
(list 2560.125 869.0639) 
(list 2560.125 869.0742) 
(list 2560.125 869.0844) 
(list 2560.125 869.0947) 
(list 2560.125 869.105) 
(list 2560.125 869.1153) 
(list 2560.125 869.1256) 
(list 2560.125 869.1358) 
(list 2560.125 869.1461) 
(list 2560.125 869.1564) 
(list 2560.125 869.1667) 
(list 2560.125 869.1769) 
(list 2560.125 869.1872) 
(list 2560.125 869.1975) 
(list 2560.125 869.2078) 
(list 2560.125 869.2181) 
(list 2560.125 869.2283) 
(list 2560.125 869.2386) 
(list 2560.125 869.2489) 
(list 2560.125 869.2592) 
(list 2560.125 869.2694) 
(list 2560.125 869.2797) 
(list 2560.125 869.29) 
(list 2560 869.29)))
(apply 'command (append '("pline") coords '("c")))
(setq tap8 (ssadd (entlast) tap8))
(command "_mirror" (entlast) "" "2560,900" "2560,901" "No")
(setq tap8 (ssadd (entlast) tap8))
(setq coords (list 
(list 2560.4778 868.92) 
(list 2560.4674 868.92) 
(list 2560.4668 868.9303) 
(list 2560.4645 868.9406) 
(list 2560.4606 868.9508) 
(list 2560.455 868.9611) 
(list 2560.4481 868.9714) 
(list 2560.4399 868.9817) 
(list 2560.4308 868.9919) 
(list 2560.421 869.0022) 
(list 2560.4108 869.0125) 
(list 2560.4005 869.0228) 
(list 2560.3905 869.0331) 
(list 2560.3809 869.0433) 
(list 2560.3722 869.0536) 
(list 2560.3646 869.0639) 
(list 2560.3584 869.0742) 
(list 2560.3537 869.0844) 
(list 2560.3507 869.0947) 
(list 2560.3495 869.105) 
(list 2560.3502 869.1153) 
(list 2560.3528 869.1256) 
(list 2560.3572 869.1358) 
(list 2560.3632 869.1461) 
(list 2560.3708 869.1564) 
(list 2560.3797 869.1667) 
(list 2560.3896 869.1769) 
(list 2560.4002 869.1872) 
(list 2560.4113 869.1975) 
(list 2560.4225 869.2078) 
(list 2560.4334 869.2181) 
(list 2560.4437 869.2283) 
(list 2560.4532 869.2386) 
(list 2560.4614 869.2489) 
(list 2560.4682 869.2592) 
(list 2560.4733 869.2694) 
(list 2560.4765 869.2797) 
(list 2560.4778 869.29) 
(list 2560.4778 869.29)))
(apply 'command (append '("pline") coords '("c")))
(setq tap8 (ssadd (entlast) tap8))
(command "_mirror" (entlast) "" "2560,900" "2560,901" "No")
(setq tap8 (ssadd (entlast) tap8))
(setq coords (list 
(list 2561.122 868.92) 
(list 2560.4778 868.92) 
(list 2560.4778 868.9303) 
(list 2560.4778 868.9406) 
(list 2560.4778 868.9508) 
(list 2560.4778 868.9611) 
(list 2560.4778 868.9714) 
(list 2560.4778 868.9817) 
(list 2560.4778 868.9919) 
(list 2560.4778 869.0022) 
(list 2560.4778 869.0125) 
(list 2560.4778 869.0228) 
(list 2560.4778 869.0331) 
(list 2560.4778 869.0433) 
(list 2560.4778 869.0536) 
(list 2560.4778 869.0639) 
(list 2560.4778 869.0742) 
(list 2560.4778 869.0844) 
(list 2560.4778 869.0947) 
(list 2560.4778 869.105) 
(list 2560.4778 869.1153) 
(list 2560.4778 869.1256) 
(list 2560.4778 869.1358) 
(list 2560.4778 869.1461) 
(list 2560.4778 869.1564) 
(list 2560.4778 869.1667) 
(list 2560.4778 869.1769) 
(list 2560.4778 869.1872) 
(list 2560.4778 869.1975) 
(list 2560.4778 869.2078) 
(list 2560.4778 869.2181) 
(list 2560.4778 869.2283) 
(list 2560.4778 869.2386) 
(list 2560.4778 869.2489) 
(list 2560.4778 869.2592) 
(list 2560.4778 869.2694) 
(list 2560.4778 869.2797) 
(list 2560.4778 869.29) 
(list 2561.122 869.29)))
(apply 'command (append '("pline") coords '("c")))
(setq tap8 (ssadd (entlast) tap8))
(command "_mirror" (entlast) "" "2560,900" "2560,901" "No")
(setq tap8 (ssadd (entlast) tap8))
(setq coords (list 
(list 2560 869.29) 
(list 2560.125 869.29) 
(list 2560.125 869.3003) 
(list 2560.125 869.3106) 
(list 2560.125 869.3208) 
(list 2560.125 869.3311) 
(list 2560.125 869.3414) 
(list 2560.125 869.3517) 
(list 2560.125 869.3619) 
(list 2560.125 869.3722) 
(list 2560.125 869.3825) 
(list 2560.125 869.3928) 
(list 2560.125 869.4031) 
(list 2560.125 869.4133) 
(list 2560.125 869.4236) 
(list 2560.125 869.4339) 
(list 2560.125 869.4442) 
(list 2560.125 869.4544) 
(list 2560.125 869.4647) 
(list 2560.125 869.475) 
(list 2560.125 869.4853) 
(list 2560.125 869.4956) 
(list 2560.125 869.5058) 
(list 2560.125 869.5161) 
(list 2560.125 869.5264) 
(list 2560.125 869.5367) 
(list 2560.125 869.5469) 
(list 2560.125 869.5572) 
(list 2560.125 869.5675) 
(list 2560.125 869.5778) 
(list 2560.125 869.5881) 
(list 2560.125 869.5983) 
(list 2560.125 869.6086) 
(list 2560.125 869.6189) 
(list 2560.125 869.6292) 
(list 2560.125 869.6394) 
(list 2560.125 869.6497) 
(list 2560.125 869.66) 
(list 2560 869.66)))
(apply 'command (append '("pline") coords '("c")))
(setq tap8 (ssadd (entlast) tap8))
(command "_mirror" (entlast) "" "2560,900" "2560,901" "No")
(setq tap8 (ssadd (entlast) tap8))
(setq coords (list 
(list 2560.4882 869.29) 
(list 2560.4778 869.29) 
(list 2560.4771 869.3003) 
(list 2560.4743 869.3106) 
(list 2560.4697 869.3208) 
(list 2560.4632 869.3311) 
(list 2560.4551 869.3414) 
(list 2560.4456 869.3517) 
(list 2560.435 869.3619) 
(list 2560.4236 869.3722) 
(list 2560.4118 869.3825) 
(list 2560.3998 869.3928) 
(list 2560.3882 869.4031) 
(list 2560.3771 869.4133) 
(list 2560.3671 869.4236) 
(list 2560.3583 869.4339) 
(list 2560.3511 869.4442) 
(list 2560.3457 869.4544) 
(list 2560.3423 869.4647) 
(list 2560.341 869.475) 
(list 2560.3418 869.4853) 
(list 2560.3448 869.4956) 
(list 2560.3499 869.5058) 
(list 2560.3569 869.5161) 
(list 2560.3656 869.5264) 
(list 2560.3759 869.5367) 
(list 2560.3873 869.5469) 
(list 2560.3995 869.5572) 
(list 2560.4122 869.5675) 
(list 2560.425 869.5778) 
(list 2560.4376 869.5881) 
(list 2560.4494 869.5983) 
(list 2560.4602 869.6086) 
(list 2560.4696 869.6189) 
(list 2560.4773 869.6292) 
(list 2560.4831 869.6394) 
(list 2560.4868 869.6497) 
(list 2560.4882 869.66) 
(list 2560.4882 869.66)))
(apply 'command (append '("pline") coords '("c")))
(setq tap8 (ssadd (entlast) tap8))
(command "_mirror" (entlast) "" "2560,900" "2560,901" "No")
(setq tap8 (ssadd (entlast) tap8))
(setq coords (list 
(list 2561.122 869.29) 
(list 2560.4882 869.29) 
(list 2560.4882 869.3003) 
(list 2560.4882 869.3106) 
(list 2560.4882 869.3208) 
(list 2560.4882 869.3311) 
(list 2560.4882 869.3414) 
(list 2560.4882 869.3517) 
(list 2560.4882 869.3619) 
(list 2560.4882 869.3722) 
(list 2560.4882 869.3825) 
(list 2560.4882 869.3928) 
(list 2560.4882 869.4031) 
(list 2560.4882 869.4133) 
(list 2560.4882 869.4236) 
(list 2560.4882 869.4339) 
(list 2560.4882 869.4442) 
(list 2560.4882 869.4544) 
(list 2560.4882 869.4647) 
(list 2560.4882 869.475) 
(list 2560.4882 869.4853) 
(list 2560.4882 869.4956) 
(list 2560.4882 869.5058) 
(list 2560.4882 869.5161) 
(list 2560.4882 869.5264) 
(list 2560.4882 869.5367) 
(list 2560.4882 869.5469) 
(list 2560.4882 869.5572) 
(list 2560.4882 869.5675) 
(list 2560.4882 869.5778) 
(list 2560.4882 869.5881) 
(list 2560.4882 869.5983) 
(list 2560.4882 869.6086) 
(list 2560.4882 869.6189) 
(list 2560.4882 869.6292) 
(list 2560.4882 869.6394) 
(list 2560.4882 869.6497) 
(list 2560.4882 869.66) 
(list 2561.122 869.66)))
(apply 'command (append '("pline") coords '("c")))
(setq tap8 (ssadd (entlast) tap8))
(command "_mirror" (entlast) "" "2560,900" "2560,901" "No")
(setq tap8 (ssadd (entlast) tap8))
(setq coords (list 
(list 2560 869.66) 
(list 2560.125 869.66) 
(list 2560.125 869.6703) 
(list 2560.125 869.6806) 
(list 2560.125 869.6908) 
(list 2560.125 869.7011) 
(list 2560.125 869.7114) 
(list 2560.125 869.7217) 
(list 2560.125 869.7319) 
(list 2560.125 869.7422) 
(list 2560.125 869.7525) 
(list 2560.125 869.7628) 
(list 2560.125 869.7731) 
(list 2560.125 869.7833) 
(list 2560.125 869.7936) 
(list 2560.125 869.8039) 
(list 2560.125 869.8142) 
(list 2560.125 869.8244) 
(list 2560.125 869.8347) 
(list 2560.125 869.845) 
(list 2560.125 869.8553) 
(list 2560.125 869.8656) 
(list 2560.125 869.8758) 
(list 2560.125 869.8861) 
(list 2560.125 869.8964) 
(list 2560.125 869.9067) 
(list 2560.125 869.9169) 
(list 2560.125 869.9272) 
(list 2560.125 869.9375) 
(list 2560.125 869.9478) 
(list 2560.125 869.9581) 
(list 2560.125 869.9683) 
(list 2560.125 869.9786) 
(list 2560.125 869.9889) 
(list 2560.125 869.9992) 
(list 2560.125 870.0094) 
(list 2560.125 870.0197) 
(list 2560.125 870.03) 
(list 2560 870.03)))
(apply 'command (append '("pline") coords '("c")))
(setq tap8 (ssadd (entlast) tap8))
(command "_mirror" (entlast) "" "2560,900" "2560,901" "No")
(setq tap8 (ssadd (entlast) tap8))
(setq coords (list 
(list 2560.4986 869.66) 
(list 2560.4882 869.66) 
(list 2560.4873 869.6703) 
(list 2560.4842 869.6806) 
(list 2560.4788 869.6908) 
(list 2560.4714 869.7011) 
(list 2560.4621 869.7114) 
(list 2560.4513 869.7217) 
(list 2560.4392 869.7319) 
(list 2560.4262 869.7422) 
(list 2560.4127 869.7525) 
(list 2560.3991 869.7628) 
(list 2560.3859 869.7731) 
(list 2560.3733 869.7833) 
(list 2560.3619 869.7936) 
(list 2560.352 869.8039) 
(list 2560.3439 869.8142) 
(list 2560.3378 869.8244) 
(list 2560.3339 869.8347) 
(list 2560.3325 869.845) 
(list 2560.3335 869.8553) 
(list 2560.3369 869.8656) 
(list 2560.3426 869.8758) 
(list 2560.3506 869.8861) 
(list 2560.3605 869.8964) 
(list 2560.3721 869.9067) 
(list 2560.385 869.9169) 
(list 2560.3988 869.9272) 
(list 2560.4132 869.9375) 
(list 2560.4276 869.9478) 
(list 2560.4417 869.9581) 
(list 2560.4551 869.9683) 
(list 2560.4672 869.9786) 
(list 2560.4778 869.9889) 
(list 2560.4864 869.9992) 
(list 2560.4929 870.0094) 
(list 2560.497 870.0197) 
(list 2560.4986 870.03) 
(list 2560.4986 870.03)))
(apply 'command (append '("pline") coords '("c")))
(setq tap8 (ssadd (entlast) tap8))
(command "_mirror" (entlast) "" "2560,900" "2560,901" "No")
(setq tap8 (ssadd (entlast) tap8))
(setq coords (list 
(list 2561.122 869.66) 
(list 2560.4986 869.66) 
(list 2560.4986 869.6703) 
(list 2560.4986 869.6806) 
(list 2560.4986 869.6908) 
(list 2560.4986 869.7011) 
(list 2560.4986 869.7114) 
(list 2560.4986 869.7217) 
(list 2560.4986 869.7319) 
(list 2560.4986 869.7422) 
(list 2560.4986 869.7525) 
(list 2560.4986 869.7628) 
(list 2560.4986 869.7731) 
(list 2560.4986 869.7833) 
(list 2560.4986 869.7936) 
(list 2560.4986 869.8039) 
(list 2560.4986 869.8142) 
(list 2560.4986 869.8244) 
(list 2560.4986 869.8347) 
(list 2560.4986 869.845) 
(list 2560.4986 869.8553) 
(list 2560.4986 869.8656) 
(list 2560.4986 869.8758) 
(list 2560.4986 869.8861) 
(list 2560.4986 869.8964) 
(list 2560.4986 869.9067) 
(list 2560.4986 869.9169) 
(list 2560.4986 869.9272) 
(list 2560.4986 869.9375) 
(list 2560.4986 869.9478) 
(list 2560.4986 869.9581) 
(list 2560.4986 869.9683) 
(list 2560.4986 869.9786) 
(list 2560.4986 869.9889) 
(list 2560.4986 869.9992) 
(list 2560.4986 870.0094) 
(list 2560.4986 870.0197) 
(list 2560.4986 870.03) 
(list 2561.122 870.03)))
(apply 'command (append '("pline") coords '("c")))
(setq tap8 (ssadd (entlast) tap8))
(command "_mirror" (entlast) "" "2560,900" "2560,901" "No")
(setq tap8 (ssadd (entlast) tap8))
(setq coords (list 
(list 2560 870.03) 
(list 2560.125 870.03) 
(list 2560.125 870.0403) 
(list 2560.125 870.0506) 
(list 2560.125 870.0608) 
(list 2560.125 870.0711) 
(list 2560.125 870.0814) 
(list 2560.125 870.0917) 
(list 2560.125 870.1019) 
(list 2560.125 870.1122) 
(list 2560.125 870.1225) 
(list 2560.125 870.1328) 
(list 2560.125 870.1431) 
(list 2560.125 870.1533) 
(list 2560.125 870.1636) 
(list 2560.125 870.1739) 
(list 2560.125 870.1842) 
(list 2560.125 870.1944) 
(list 2560.125 870.2047) 
(list 2560.125 870.215) 
(list 2560.125 870.2253) 
(list 2560.125 870.2356) 
(list 2560.125 870.2458) 
(list 2560.125 870.2561) 
(list 2560.125 870.2664) 
(list 2560.125 870.2767) 
(list 2560.125 870.2869) 
(list 2560.125 870.2972) 
(list 2560.125 870.3075) 
(list 2560.125 870.3178) 
(list 2560.125 870.3281) 
(list 2560.125 870.3383) 
(list 2560.125 870.3486) 
(list 2560.125 870.3589) 
(list 2560.125 870.3692) 
(list 2560.125 870.3794) 
(list 2560.125 870.3897) 
(list 2560.125 870.4) 
(list 2560 870.4)))
(apply 'command (append '("pline") coords '("c")))
(setq tap8 (ssadd (entlast) tap8))
(command "_mirror" (entlast) "" "2560,900" "2560,901" "No")
(setq tap8 (ssadd (entlast) tap8))
(setq coords (list 
(list 2560.509 870.03) 
(list 2560.4986 870.03) 
(list 2560.4976 870.0403) 
(list 2560.494 870.0506) 
(list 2560.4879 870.0608) 
(list 2560.4796 870.0711) 
(list 2560.4691 870.0814) 
(list 2560.4569 870.0917) 
(list 2560.4434 870.1019) 
(list 2560.4288 870.1122) 
(list 2560.4136 870.1225) 
(list 2560.3984 870.1328) 
(list 2560.3836 870.1431) 
(list 2560.3695 870.1533) 
(list 2560.3568 870.1636) 
(list 2560.3457 870.1739) 
(list 2560.3366 870.1842) 
(list 2560.3298 870.1944) 
(list 2560.3255 870.2047) 
(list 2560.3239 870.215) 
(list 2560.3251 870.2253) 
(list 2560.3289 870.2356) 
(list 2560.3354 870.2458) 
(list 2560.3443 870.2561) 
(list 2560.3553 870.2664) 
(list 2560.3683 870.2767) 
(list 2560.3827 870.2869) 
(list 2560.3981 870.2972) 
(list 2560.4141 870.3075) 
(list 2560.4302 870.3178) 
(list 2560.4459 870.3281) 
(list 2560.4607 870.3383) 
(list 2560.4742 870.3486) 
(list 2560.4859 870.3589) 
(list 2560.4956 870.3692) 
(list 2560.5027 870.3794) 
(list 2560.5073 870.3897) 
(list 2560.509 870.4) 
(list 2560.509 870.4)))
(apply 'command (append '("pline") coords '("c")))
(setq tap8 (ssadd (entlast) tap8))
(command "_mirror" (entlast) "" "2560,900" "2560,901" "No")
(setq tap8 (ssadd (entlast) tap8))
(setq coords (list 
(list 2561.122 870.03) 
(list 2560.509 870.03) 
(list 2560.509 870.0403) 
(list 2560.509 870.0506) 
(list 2560.509 870.0608) 
(list 2560.509 870.0711) 
(list 2560.509 870.0814) 
(list 2560.509 870.0917) 
(list 2560.509 870.1019) 
(list 2560.509 870.1122) 
(list 2560.509 870.1225) 
(list 2560.509 870.1328) 
(list 2560.509 870.1431) 
(list 2560.509 870.1533) 
(list 2560.509 870.1636) 
(list 2560.509 870.1739) 
(list 2560.509 870.1842) 
(list 2560.509 870.1944) 
(list 2560.509 870.2047) 
(list 2560.509 870.215) 
(list 2560.509 870.2253) 
(list 2560.509 870.2356) 
(list 2560.509 870.2458) 
(list 2560.509 870.2561) 
(list 2560.509 870.2664) 
(list 2560.509 870.2767) 
(list 2560.509 870.2869) 
(list 2560.509 870.2972) 
(list 2560.509 870.3075) 
(list 2560.509 870.3178) 
(list 2560.509 870.3281) 
(list 2560.509 870.3383) 
(list 2560.509 870.3486) 
(list 2560.509 870.3589) 
(list 2560.509 870.3692) 
(list 2560.509 870.3794) 
(list 2560.509 870.3897) 
(list 2560.509 870.4) 
(list 2561.122 870.4)))
(apply 'command (append '("pline") coords '("c")))
(setq tap8 (ssadd (entlast) tap8))
(command "_mirror" (entlast) "" "2560,900" "2560,901" "No")
(setq tap8 (ssadd (entlast) tap8))
(setq coords (list 
(list 2560 870.4) 
(list 2560.125 870.4) 
(list 2560.125 870.4103) 
(list 2560.125 870.4206) 
(list 2560.125 870.4308) 
(list 2560.125 870.4411) 
(list 2560.125 870.4514) 
(list 2560.125 870.4617) 
(list 2560.125 870.4719) 
(list 2560.125 870.4822) 
(list 2560.125 870.4925) 
(list 2560.125 870.5028) 
(list 2560.125 870.5131) 
(list 2560.125 870.5233) 
(list 2560.125 870.5336) 
(list 2560.125 870.5439) 
(list 2560.125 870.5542) 
(list 2560.125 870.5644) 
(list 2560.125 870.5747) 
(list 2560.125 870.585) 
(list 2560.125 870.5953) 
(list 2560.125 870.6056) 
(list 2560.125 870.6158) 
(list 2560.125 870.6261) 
(list 2560.125 870.6364) 
(list 2560.125 870.6467) 
(list 2560.125 870.6569) 
(list 2560.125 870.6672) 
(list 2560.125 870.6775) 
(list 2560.125 870.6878) 
(list 2560.125 870.6981) 
(list 2560.125 870.7083) 
(list 2560.125 870.7186) 
(list 2560.125 870.7289) 
(list 2560.125 870.7392) 
(list 2560.125 870.7494) 
(list 2560.125 870.7597) 
(list 2560.125 870.77) 
(list 2560 870.77)))
(apply 'command (append '("pline") coords '("c")))
(setq tap8 (ssadd (entlast) tap8))
(command "_mirror" (entlast) "" "2560,900" "2560,901" "No")
(setq tap8 (ssadd (entlast) tap8))
(setq coords (list 
(list 2560.5194 870.4) 
(list 2560.509 870.4) 
(list 2560.5078 870.4103) 
(list 2560.5038 870.4206) 
(list 2560.4971 870.4308) 
(list 2560.4878 870.4411) 
(list 2560.4762 870.4514) 
(list 2560.4626 870.4617) 
(list 2560.4475 870.4719) 
(list 2560.4313 870.4822) 
(list 2560.4146 870.4925) 
(list 2560.3977 870.5028) 
(list 2560.3813 870.5131) 
(list 2560.3657 870.5233) 
(list 2560.3516 870.5336) 
(list 2560.3394 870.5439) 
(list 2560.3293 870.5542) 
(list 2560.3218 870.5644) 
(list 2560.3171 870.5747) 
(list 2560.3154 870.585) 
(list 2560.3167 870.5953) 
(list 2560.321 870.6056) 
(list 2560.3281 870.6158) 
(list 2560.338 870.6261) 
(list 2560.3502 870.6364) 
(list 2560.3645 870.6467) 
(list 2560.3804 870.6569) 
(list 2560.3974 870.6672) 
(list 2560.415 870.6775) 
(list 2560.4328 870.6878) 
(list 2560.4501 870.6981) 
(list 2560.4664 870.7083) 
(list 2560.4812 870.7186) 
(list 2560.4941 870.7289) 
(list 2560.5047 870.7392) 
(list 2560.5126 870.7494) 
(list 2560.5175 870.7597) 
(list 2560.5194 870.77) 
(list 2560.5194 870.77)))
(apply 'command (append '("pline") coords '("c")))
(setq tap8 (ssadd (entlast) tap8))
(command "_mirror" (entlast) "" "2560,900" "2560,901" "No")
(setq tap8 (ssadd (entlast) tap8))
(setq coords (list 
(list 2561.122 870.4) 
(list 2560.5194 870.4) 
(list 2560.5194 870.4103) 
(list 2560.5194 870.4206) 
(list 2560.5194 870.4308) 
(list 2560.5194 870.4411) 
(list 2560.5194 870.4514) 
(list 2560.5194 870.4617) 
(list 2560.5194 870.4719) 
(list 2560.5194 870.4822) 
(list 2560.5194 870.4925) 
(list 2560.5194 870.5028) 
(list 2560.5194 870.5131) 
(list 2560.5194 870.5233) 
(list 2560.5194 870.5336) 
(list 2560.5194 870.5439) 
(list 2560.5194 870.5542) 
(list 2560.5194 870.5644) 
(list 2560.5194 870.5747) 
(list 2560.5194 870.585) 
(list 2560.5194 870.5953) 
(list 2560.5194 870.6056) 
(list 2560.5194 870.6158) 
(list 2560.5194 870.6261) 
(list 2560.5194 870.6364) 
(list 2560.5194 870.6467) 
(list 2560.5194 870.6569) 
(list 2560.5194 870.6672) 
(list 2560.5194 870.6775) 
(list 2560.5194 870.6878) 
(list 2560.5194 870.6981) 
(list 2560.5194 870.7083) 
(list 2560.5194 870.7186) 
(list 2560.5194 870.7289) 
(list 2560.5194 870.7392) 
(list 2560.5194 870.7494) 
(list 2560.5194 870.7597) 
(list 2560.5194 870.77) 
(list 2561.122 870.77)))
(apply 'command (append '("pline") coords '("c")))
(setq tap8 (ssadd (entlast) tap8))
(command "_mirror" (entlast) "" "2560,900" "2560,901" "No")
(setq tap8 (ssadd (entlast) tap8))
(setq coords (list 
(list 2560 870.77) 
(list 2560.125 870.77) 
(list 2560.125 870.7803) 
(list 2560.125 870.7906) 
(list 2560.125 870.8008) 
(list 2560.125 870.8111) 
(list 2560.125 870.8214) 
(list 2560.125 870.8317) 
(list 2560.125 870.8419) 
(list 2560.125 870.8522) 
(list 2560.125 870.8625) 
(list 2560.125 870.8728) 
(list 2560.125 870.8831) 
(list 2560.125 870.8933) 
(list 2560.125 870.9036) 
(list 2560.125 870.9139) 
(list 2560.125 870.9242) 
(list 2560.125 870.9344) 
(list 2560.125 870.9447) 
(list 2560.125 870.955) 
(list 2560.125 870.9653) 
(list 2560.125 870.9756) 
(list 2560.125 870.9858) 
(list 2560.125 870.9961) 
(list 2560.125 871.0064) 
(list 2560.125 871.0167) 
(list 2560.125 871.0269) 
(list 2560.125 871.0372) 
(list 2560.125 871.0475) 
(list 2560.125 871.0578) 
(list 2560.125 871.0681) 
(list 2560.125 871.0783) 
(list 2560.125 871.0886) 
(list 2560.125 871.0989) 
(list 2560.125 871.1092) 
(list 2560.125 871.1194) 
(list 2560.125 871.1297) 
(list 2560.125 871.14) 
(list 2560 871.14)))
(apply 'command (append '("pline") coords '("c")))
(setq tap8 (ssadd (entlast) tap8))
(command "_mirror" (entlast) "" "2560,900" "2560,901" "No")
(setq tap8 (ssadd (entlast) tap8))
(setq coords (list 
(list 2560.5298 870.77) 
(list 2560.5194 870.77) 
(list 2560.5181 870.7803) 
(list 2560.5137 870.7906) 
(list 2560.5062 870.8008) 
(list 2560.4959 870.8111) 
(list 2560.4832 870.8214) 
(list 2560.4683 870.8317) 
(list 2560.4517 870.8419) 
(list 2560.4339 870.8522) 
(list 2560.4155 870.8625) 
(list 2560.397 870.8728) 
(list 2560.3789 870.8831) 
(list 2560.3619 870.8933) 
(list 2560.3465 870.9036) 
(list 2560.333 870.9139) 
(list 2560.3221 870.9242) 
(list 2560.3139 870.9344) 
(list 2560.3088 870.9447) 
(list 2560.3069 870.955) 
(list 2560.3083 870.9653) 
(list 2560.313 870.9756) 
(list 2560.3208 870.9858) 
(list 2560.3316 870.9961) 
(list 2560.345 871.0064) 
(list 2560.3607 871.0167) 
(list 2560.378 871.0269) 
(list 2560.3967 871.0372) 
(list 2560.416 871.0475) 
(list 2560.4354 871.0578) 
(list 2560.4542 871.0681) 
(list 2560.4721 871.0783) 
(list 2560.4882 871.0886) 
(list 2560.5023 871.0989) 
(list 2560.5138 871.1092) 
(list 2560.5224 871.1194) 
(list 2560.5278 871.1297) 
(list 2560.5298 871.14) 
(list 2560.5298 871.14)))
(apply 'command (append '("pline") coords '("c")))
(setq tap8 (ssadd (entlast) tap8))
(command "_mirror" (entlast) "" "2560,900" "2560,901" "No")
(setq tap8 (ssadd (entlast) tap8))
(setq coords (list 
(list 2561.122 870.77) 
(list 2560.5298 870.77) 
(list 2560.5298 870.7803) 
(list 2560.5298 870.7906) 
(list 2560.5298 870.8008) 
(list 2560.5298 870.8111) 
(list 2560.5298 870.8214) 
(list 2560.5298 870.8317) 
(list 2560.5298 870.8419) 
(list 2560.5298 870.8522) 
(list 2560.5298 870.8625) 
(list 2560.5298 870.8728) 
(list 2560.5298 870.8831) 
(list 2560.5298 870.8933) 
(list 2560.5298 870.9036) 
(list 2560.5298 870.9139) 
(list 2560.5298 870.9242) 
(list 2560.5298 870.9344) 
(list 2560.5298 870.9447) 
(list 2560.5298 870.955) 
(list 2560.5298 870.9653) 
(list 2560.5298 870.9756) 
(list 2560.5298 870.9858) 
(list 2560.5298 870.9961) 
(list 2560.5298 871.0064) 
(list 2560.5298 871.0167) 
(list 2560.5298 871.0269) 
(list 2560.5298 871.0372) 
(list 2560.5298 871.0475) 
(list 2560.5298 871.0578) 
(list 2560.5298 871.0681) 
(list 2560.5298 871.0783) 
(list 2560.5298 871.0886) 
(list 2560.5298 871.0989) 
(list 2560.5298 871.1092) 
(list 2560.5298 871.1194) 
(list 2560.5298 871.1297) 
(list 2560.5298 871.14) 
(list 2561.122 871.14)))
(apply 'command (append '("pline") coords '("c")))
(setq tap8 (ssadd (entlast) tap8))
(command "_mirror" (entlast) "" "2560,900" "2560,901" "No")
(setq tap8 (ssadd (entlast) tap8))
(setq coords (list 
(list 2560 871.14) 
(list 2560.125 871.14) 
(list 2560.125 871.1503) 
(list 2560.125 871.1606) 
(list 2560.125 871.1708) 
(list 2560.125 871.1811) 
(list 2560.125 871.1914) 
(list 2560.125 871.2017) 
(list 2560.125 871.2119) 
(list 2560.125 871.2222) 
(list 2560.125 871.2325) 
(list 2560.125 871.2428) 
(list 2560.125 871.2531) 
(list 2560.125 871.2633) 
(list 2560.125 871.2736) 
(list 2560.125 871.2839) 
(list 2560.125 871.2942) 
(list 2560.125 871.3044) 
(list 2560.125 871.3147) 
(list 2560.125 871.325) 
(list 2560.125 871.3353) 
(list 2560.125 871.3456) 
(list 2560.125 871.3558) 
(list 2560.125 871.3661) 
(list 2560.125 871.3764) 
(list 2560.125 871.3867) 
(list 2560.125 871.3969) 
(list 2560.125 871.4072) 
(list 2560.125 871.4175) 
(list 2560.125 871.4278) 
(list 2560.125 871.4381) 
(list 2560.125 871.4483) 
(list 2560.125 871.4586) 
(list 2560.125 871.4689) 
(list 2560.125 871.4792) 
(list 2560.125 871.4894) 
(list 2560.125 871.4997) 
(list 2560.125 871.51) 
(list 2560 871.51)))
(apply 'command (append '("pline") coords '("c")))
(setq tap8 (ssadd (entlast) tap8))
(command "_mirror" (entlast) "" "2560,900" "2560,901" "No")
(setq tap8 (ssadd (entlast) tap8))
(setq coords (list 
(list 2560.5402 871.14) 
(list 2560.5298 871.14) 
(list 2560.5284 871.1503) 
(list 2560.5235 871.1606) 
(list 2560.5153 871.1708) 
(list 2560.5041 871.1811) 
(list 2560.4902 871.1914) 
(list 2560.4739 871.2017) 
(list 2560.4559 871.2119) 
(list 2560.4365 871.2222) 
(list 2560.4164 871.2325) 
(list 2560.3963 871.2428) 
(list 2560.3766 871.2531) 
(list 2560.3581 871.2633) 
(list 2560.3413 871.2736) 
(list 2560.3267 871.2839) 
(list 2560.3148 871.2942) 
(list 2560.3059 871.3044) 
(list 2560.3004 871.3147) 
(list 2560.2983 871.325) 
(list 2560.2999 871.3353) 
(list 2560.305 871.3456) 
(list 2560.3136 871.3558) 
(list 2560.3253 871.3661) 
(list 2560.3399 871.3764) 
(list 2560.3569 871.3867) 
(list 2560.3757 871.3969) 
(list 2560.396 871.4072) 
(list 2560.4169 871.4175) 
(list 2560.4379 871.4278) 
(list 2560.4584 871.4381) 
(list 2560.4777 871.4483) 
(list 2560.4953 871.4586) 
(list 2560.5105 871.4689) 
(list 2560.523 871.4792) 
(list 2560.5322 871.4894) 
(list 2560.538 871.4997) 
(list 2560.5402 871.51) 
(list 2560.5402 871.51)))
(apply 'command (append '("pline") coords '("c")))
(setq tap8 (ssadd (entlast) tap8))
(command "_mirror" (entlast) "" "2560,900" "2560,901" "No")
(setq tap8 (ssadd (entlast) tap8))
(setq coords (list 
(list 2561.122 871.14) 
(list 2560.5402 871.14) 
(list 2560.5402 871.1503) 
(list 2560.5402 871.1606) 
(list 2560.5402 871.1708) 
(list 2560.5402 871.1811) 
(list 2560.5402 871.1914) 
(list 2560.5402 871.2017) 
(list 2560.5402 871.2119) 
(list 2560.5402 871.2222) 
(list 2560.5402 871.2325) 
(list 2560.5402 871.2428) 
(list 2560.5402 871.2531) 
(list 2560.5402 871.2633) 
(list 2560.5402 871.2736) 
(list 2560.5402 871.2839) 
(list 2560.5402 871.2942) 
(list 2560.5402 871.3044) 
(list 2560.5402 871.3147) 
(list 2560.5402 871.325) 
(list 2560.5402 871.3353) 
(list 2560.5402 871.3456) 
(list 2560.5402 871.3558) 
(list 2560.5402 871.3661) 
(list 2560.5402 871.3764) 
(list 2560.5402 871.3867) 
(list 2560.5402 871.3969) 
(list 2560.5402 871.4072) 
(list 2560.5402 871.4175) 
(list 2560.5402 871.4278) 
(list 2560.5402 871.4381) 
(list 2560.5402 871.4483) 
(list 2560.5402 871.4586) 
(list 2560.5402 871.4689) 
(list 2560.5402 871.4792) 
(list 2560.5402 871.4894) 
(list 2560.5402 871.4997) 
(list 2560.5402 871.51) 
(list 2561.122 871.51)))
(apply 'command (append '("pline") coords '("c")))
(setq tap8 (ssadd (entlast) tap8))
(command "_mirror" (entlast) "" "2560,900" "2560,901" "No")
(setq tap8 (ssadd (entlast) tap8))
(setq coords (list 
(list 2560 871.51) 
(list 2560.125 871.51) 
(list 2560.125 871.5203) 
(list 2560.125 871.5306) 
(list 2560.125 871.5408) 
(list 2560.125 871.5511) 
(list 2560.125 871.5614) 
(list 2560.125 871.5717) 
(list 2560.125 871.5819) 
(list 2560.125 871.5922) 
(list 2560.125 871.6025) 
(list 2560.125 871.6128) 
(list 2560.125 871.6231) 
(list 2560.125 871.6333) 
(list 2560.125 871.6436) 
(list 2560.125 871.6539) 
(list 2560.125 871.6642) 
(list 2560.125 871.6744) 
(list 2560.125 871.6847) 
(list 2560.125 871.695) 
(list 2560.125 871.7053) 
(list 2560.125 871.7156) 
(list 2560.125 871.7258) 
(list 2560.125 871.7361) 
(list 2560.125 871.7464) 
(list 2560.125 871.7567) 
(list 2560.125 871.7669) 
(list 2560.125 871.7772) 
(list 2560.125 871.7875) 
(list 2560.125 871.7978) 
(list 2560.125 871.8081) 
(list 2560.125 871.8183) 
(list 2560.125 871.8286) 
(list 2560.125 871.8389) 
(list 2560.125 871.8492) 
(list 2560.125 871.8594) 
(list 2560.125 871.8697) 
(list 2560.125 871.88) 
(list 2560 871.88)))
(apply 'command (append '("pline") coords '("c")))
(setq tap8 (ssadd (entlast) tap8))
(command "_mirror" (entlast) "" "2560,900" "2560,901" "No")
(setq tap8 (ssadd (entlast) tap8))
(setq coords (list 
(list 2560.5506 871.51) 
(list 2560.5402 871.51) 
(list 2560.5386 871.5203) 
(list 2560.5333 871.5306) 
(list 2560.5245 871.5408) 
(list 2560.5123 871.5511) 
(list 2560.4972 871.5614) 
(list 2560.4796 871.5717) 
(list 2560.46 871.5819) 
(list 2560.4391 871.5922) 
(list 2560.4174 871.6025) 
(list 2560.3956 871.6128) 
(list 2560.3743 871.6231) 
(list 2560.3543 871.6333) 
(list 2560.3362 871.6436) 
(list 2560.3204 871.6539) 
(list 2560.3075 871.6642) 
(list 2560.2979 871.6744) 
(list 2560.292 871.6847) 
(list 2560.2898 871.695) 
(list 2560.2915 871.7053) 
(list 2560.2971 871.7156) 
(list 2560.3063 871.7258) 
(list 2560.319 871.7361) 
(list 2560.3347 871.7464) 
(list 2560.3531 871.7567) 
(list 2560.3734 871.7669) 
(list 2560.3953 871.7772) 
(list 2560.4178 871.7875) 
(list 2560.4405 871.7978) 
(list 2560.4626 871.8081) 
(list 2560.4834 871.8183) 
(list 2560.5023 871.8286) 
(list 2560.5187 871.8389) 
(list 2560.5321 871.8492) 
(list 2560.5421 871.8594) 
(list 2560.5483 871.8697) 
(list 2560.5506 871.88) 
(list 2560.5506 871.88)))
(apply 'command (append '("pline") coords '("c")))
(setq tap8 (ssadd (entlast) tap8))
(command "_mirror" (entlast) "" "2560,900" "2560,901" "No")
(setq tap8 (ssadd (entlast) tap8))
(setq coords (list 
(list 2561.122 871.51) 
(list 2560.5506 871.51) 
(list 2560.5506 871.5203) 
(list 2560.5506 871.5306) 
(list 2560.5506 871.5408) 
(list 2560.5506 871.5511) 
(list 2560.5506 871.5614) 
(list 2560.5506 871.5717) 
(list 2560.5506 871.5819) 
(list 2560.5506 871.5922) 
(list 2560.5506 871.6025) 
(list 2560.5506 871.6128) 
(list 2560.5506 871.6231) 
(list 2560.5506 871.6333) 
(list 2560.5506 871.6436) 
(list 2560.5506 871.6539) 
(list 2560.5506 871.6642) 
(list 2560.5506 871.6744) 
(list 2560.5506 871.6847) 
(list 2560.5506 871.695) 
(list 2560.5506 871.7053) 
(list 2560.5506 871.7156) 
(list 2560.5506 871.7258) 
(list 2560.5506 871.7361) 
(list 2560.5506 871.7464) 
(list 2560.5506 871.7567) 
(list 2560.5506 871.7669) 
(list 2560.5506 871.7772) 
(list 2560.5506 871.7875) 
(list 2560.5506 871.7978) 
(list 2560.5506 871.8081) 
(list 2560.5506 871.8183) 
(list 2560.5506 871.8286) 
(list 2560.5506 871.8389) 
(list 2560.5506 871.8492) 
(list 2560.5506 871.8594) 
(list 2560.5506 871.8697) 
(list 2560.5506 871.88) 
(list 2561.122 871.88)))
(apply 'command (append '("pline") coords '("c")))
(setq tap8 (ssadd (entlast) tap8))
(command "_mirror" (entlast) "" "2560,900" "2560,901" "No")
(setq tap8 (ssadd (entlast) tap8))
(setq coords (list 
(list 2560 871.88) 
(list 2560.125 871.88) 
(list 2560.125 871.8903) 
(list 2560.125 871.9006) 
(list 2560.125 871.9108) 
(list 2560.125 871.9211) 
(list 2560.125 871.9314) 
(list 2560.125 871.9417) 
(list 2560.125 871.9519) 
(list 2560.125 871.9622) 
(list 2560.125 871.9725) 
(list 2560.125 871.9828) 
(list 2560.125 871.9931) 
(list 2560.125 872.0033) 
(list 2560.125 872.0136) 
(list 2560.125 872.0239) 
(list 2560.125 872.0342) 
(list 2560.125 872.0444) 
(list 2560.125 872.0547) 
(list 2560.125 872.065) 
(list 2560.125 872.0753) 
(list 2560.125 872.0856) 
(list 2560.125 872.0958) 
(list 2560.125 872.1061) 
(list 2560.125 872.1164) 
(list 2560.125 872.1267) 
(list 2560.125 872.1369) 
(list 2560.125 872.1472) 
(list 2560.125 872.1575) 
(list 2560.125 872.1678) 
(list 2560.125 872.1781) 
(list 2560.125 872.1883) 
(list 2560.125 872.1986) 
(list 2560.125 872.2089) 
(list 2560.125 872.2192) 
(list 2560.125 872.2294) 
(list 2560.125 872.2397) 
(list 2560.125 872.25) 
(list 2560 872.25)))
(apply 'command (append '("pline") coords '("c")))
(setq tap8 (ssadd (entlast) tap8))
(command "_mirror" (entlast) "" "2560,900" "2560,901" "No")
(setq tap8 (ssadd (entlast) tap8))
(setq coords (list 
(list 2560.561 871.88) 
(list 2560.5506 871.88) 
(list 2560.5489 871.8903) 
(list 2560.5432 871.9006) 
(list 2560.5336 871.9108) 
(list 2560.5205 871.9211) 
(list 2560.5042 871.9314) 
(list 2560.4853 871.9417) 
(list 2560.4642 871.9519) 
(list 2560.4417 871.9622) 
(list 2560.4183 871.9725) 
(list 2560.3949 871.9828) 
(list 2560.372 871.9931) 
(list 2560.3505 872.0033) 
(list 2560.331 872.0136) 
(list 2560.3141 872.0239) 
(list 2560.3003 872.0342) 
(list 2560.29 872.0444) 
(list 2560.2836 872.0547) 
(list 2560.2813 872.065) 
(list 2560.2831 872.0753) 
(list 2560.2891 872.0856) 
(list 2560.2991 872.0958) 
(list 2560.3127 872.1061) 
(list 2560.3296 872.1164) 
(list 2560.3493 872.1267) 
(list 2560.3711 872.1369) 
(list 2560.3945 872.1472) 
(list 2560.4188 872.1575) 
(list 2560.4431 872.1678) 
(list 2560.4668 872.1781) 
(list 2560.4891 872.1883) 
(list 2560.5093 872.1986) 
(list 2560.5269 872.2089) 
(list 2560.5412 872.2192) 
(list 2560.5519 872.2294) 
(list 2560.5586 872.2397) 
(list 2560.561 872.25) 
(list 2560.561 872.25)))
(apply 'command (append '("pline") coords '("c")))
(setq tap8 (ssadd (entlast) tap8))
(command "_mirror" (entlast) "" "2560,900" "2560,901" "No")
(setq tap8 (ssadd (entlast) tap8))
(setq coords (list 
(list 2561.122 871.88) 
(list 2560.561 871.88) 
(list 2560.561 871.8903) 
(list 2560.561 871.9006) 
(list 2560.561 871.9108) 
(list 2560.561 871.9211) 
(list 2560.561 871.9314) 
(list 2560.561 871.9417) 
(list 2560.561 871.9519) 
(list 2560.561 871.9622) 
(list 2560.561 871.9725) 
(list 2560.561 871.9828) 
(list 2560.561 871.9931) 
(list 2560.561 872.0033) 
(list 2560.561 872.0136) 
(list 2560.561 872.0239) 
(list 2560.561 872.0342) 
(list 2560.561 872.0444) 
(list 2560.561 872.0547) 
(list 2560.561 872.065) 
(list 2560.561 872.0753) 
(list 2560.561 872.0856) 
(list 2560.561 872.0958) 
(list 2560.561 872.1061) 
(list 2560.561 872.1164) 
(list 2560.561 872.1267) 
(list 2560.561 872.1369) 
(list 2560.561 872.1472) 
(list 2560.561 872.1575) 
(list 2560.561 872.1678) 
(list 2560.561 872.1781) 
(list 2560.561 872.1883) 
(list 2560.561 872.1986) 
(list 2560.561 872.2089) 
(list 2560.561 872.2192) 
(list 2560.561 872.2294) 
(list 2560.561 872.2397) 
(list 2560.561 872.25) 
(list 2561.122 872.25)))
(apply 'command (append '("pline") coords '("c")))
(setq tap8 (ssadd (entlast) tap8))
(command "_mirror" (entlast) "" "2560,900" "2560,901" "No")
(setq tap8 (ssadd (entlast) tap8))
(command "_block" "blktap8" "2560,900" tap8 "")
(command "_insert" "blktap8" "2560,900" "1" "1" "0")
(command "_insert" "blktap8" "2560,900" "1" "1" "180")
(setq uc8 nil)
(setq uc8 (ssadd))
(setq coords (list 
(list 0 -0.185) 
(list 0.125 -0.185) 
(list 0.125 -0.17472) 
(list 0.125 -0.16444) 
(list 0.125 -0.15417) 
(list 0.125 -0.14389) 
(list 0.125 -0.13361) 
(list 0.125 -0.12333) 
(list 0.125 -0.11306) 
(list 0.125 -0.10278) 
(list 0.125 -0.0925) 
(list 0.125 -0.082222) 
(list 0.125 -0.071944) 
(list 0.125 -0.061667) 
(list 0.125 -0.051389) 
(list 0.125 -0.041111) 
(list 0.125 -0.030833) 
(list 0.125 -0.020556) 
(list 0.125 -0.010278) 
(list 0.125 0) 
(list 0.125 0.010278) 
(list 0.125 0.020556) 
(list 0.125 0.030833) 
(list 0.125 0.041111) 
(list 0.125 0.051389) 
(list 0.125 0.061667) 
(list 0.125 0.071944) 
(list 0.125 0.082222) 
(list 0.125 0.0925) 
(list 0.125 0.10278) 
(list 0.125 0.11306) 
(list 0.125 0.12333) 
(list 0.125 0.13361) 
(list 0.125 0.14389) 
(list 0.125 0.15417) 
(list 0.125 0.16444) 
(list 0.125 0.17472) 
(list 0.125 0.185) 
(list 0 0.185)))
(apply 'command (append '("pline") coords '("c")))
(setq uc8 (ssadd (entlast) uc8))
(setq coords (list 
(list 1.122 -0.185) 
(list 0.561 -0.185) 
(list 0.55884 -0.17472) 
(list 0.55244 -0.16444) 
(list 0.54198 -0.15417) 
(list 0.52778 -0.14389) 
(list 0.51028 -0.13361) 
(list 0.49 -0.12333) 
(list 0.46757 -0.11306) 
(list 0.44366 -0.10278) 
(list 0.419 -0.0925) 
(list 0.39434 -0.082222) 
(list 0.37043 -0.071944) 
(list 0.348 -0.061667) 
(list 0.32772 -0.051389) 
(list 0.31022 -0.041111) 
(list 0.29602 -0.030833) 
(list 0.28556 -0.020556) 
(list 0.27916 -0.010278) 
(list 0.277 0) 
(list 0.27916 0.010278) 
(list 0.28556 0.020556) 
(list 0.29602 0.030833) 
(list 0.31022 0.041111) 
(list 0.32772 0.051389) 
(list 0.348 0.061667) 
(list 0.37043 0.071944) 
(list 0.39434 0.082222) 
(list 0.419 0.0925) 
(list 0.44366 0.10278) 
(list 0.46757 0.11306) 
(list 0.49 0.12333) 
(list 0.51028 0.13361) 
(list 0.52778 0.14389) 
(list 0.54198 0.15417) 
(list 0.55244 0.16444) 
(list 0.55884 0.17472) 
(list 0.561 0.185) 
(list 1.122 0.185)))
(apply 'command (append '("pline") coords '("c")))
(setq uc8 (ssadd (entlast) uc8))
(command "_block" "blkuc8" "0,0.185" uc8 "")
(command "_insert" "blkuc8" "2560,872.62" "1" "1" "0")
(command "_insert" "blkuc8" "2560,872.25" "1" "1" "180")
(command "_insert" "blkuc8" "2560,872.99" "1" "1" "0")
(command "_insert" "blkuc8" "2560,872.62" "1" "1" "180")
(command "_insert" "blkuc8" "2560,873.36" "1" "1" "0")
(command "_insert" "blkuc8" "2560,872.99" "1" "1" "180")
(command "_insert" "blkuc8" "2560,873.73" "1" "1" "0")
(command "_insert" "blkuc8" "2560,873.36" "1" "1" "180")
(command "_insert" "blkuc8" "2560,874.1" "1" "1" "0")
(command "_insert" "blkuc8" "2560,873.73" "1" "1" "180")
(command "_insert" "blkuc8" "2560,874.47" "1" "1" "0")
(command "_insert" "blkuc8" "2560,874.1" "1" "1" "180")
(command "_insert" "blkuc8" "2560,874.84" "1" "1" "0")
(command "_insert" "blkuc8" "2560,874.47" "1" "1" "180")
(command "_insert" "blkuc8" "2560,875.21" "1" "1" "0")
(command "_insert" "blkuc8" "2560,874.84" "1" "1" "180")
(command "_insert" "blkuc8" "2560,875.58" "1" "1" "0")
(command "_insert" "blkuc8" "2560,875.21" "1" "1" "180")
(command "_insert" "blkuc8" "2560,875.95" "1" "1" "0")
(command "_insert" "blkuc8" "2560,875.58" "1" "1" "180")
(command "_insert" "blkuc8" "2560,876.32" "1" "1" "0")
(command "_insert" "blkuc8" "2560,875.95" "1" "1" "180")
(command "_insert" "blkuc8" "2560,876.69" "1" "1" "0")
(command "_insert" "blkuc8" "2560,876.32" "1" "1" "180")
(command "_insert" "blkuc8" "2560,877.06" "1" "1" "0")
(command "_insert" "blkuc8" "2560,876.69" "1" "1" "180")
(command "_insert" "blkuc8" "2560,877.43" "1" "1" "0")
(command "_insert" "blkuc8" "2560,877.06" "1" "1" "180")
(command "_insert" "blkuc8" "2560,877.8" "1" "1" "0")
(command "_insert" "blkuc8" "2560,877.43" "1" "1" "180")
(command "_insert" "blkuc8" "2560,878.17" "1" "1" "0")
(command "_insert" "blkuc8" "2560,877.8" "1" "1" "180")
(command "_insert" "blkuc8" "2560,878.54" "1" "1" "0")
(command "_insert" "blkuc8" "2560,878.17" "1" "1" "180")
(command "_insert" "blkuc8" "2560,878.91" "1" "1" "0")
(command "_insert" "blkuc8" "2560,878.54" "1" "1" "180")
(command "_insert" "blkuc8" "2560,879.28" "1" "1" "0")
(command "_insert" "blkuc8" "2560,878.91" "1" "1" "180")
(command "_insert" "blkuc8" "2560,879.65" "1" "1" "0")
(command "_insert" "blkuc8" "2560,879.28" "1" "1" "180")
(command "_insert" "blkuc8" "2560,880.02" "1" "1" "0")
(command "_insert" "blkuc8" "2560,879.65" "1" "1" "180")
(command "_insert" "blkuc8" "2560,880.39" "1" "1" "0")
(command "_insert" "blkuc8" "2560,880.02" "1" "1" "180")
(command "_insert" "blkuc8" "2560,880.76" "1" "1" "0")
(command "_insert" "blkuc8" "2560,880.39" "1" "1" "180")
(command "_insert" "blkuc8" "2560,881.13" "1" "1" "0")
(command "_insert" "blkuc8" "2560,880.76" "1" "1" "180")
(command "_insert" "blkuc8" "2560,881.5" "1" "1" "0")
(command "_insert" "blkuc8" "2560,881.13" "1" "1" "180")
(command "_insert" "blkuc8" "2560,881.87" "1" "1" "0")
(command "_insert" "blkuc8" "2560,881.5" "1" "1" "180")
(command "_insert" "blkuc8" "2560,882.24" "1" "1" "0")
(command "_insert" "blkuc8" "2560,881.87" "1" "1" "180")
(command "_insert" "blkuc8" "2560,882.61" "1" "1" "0")
(command "_insert" "blkuc8" "2560,882.24" "1" "1" "180")
(command "_insert" "blkuc8" "2560,882.98" "1" "1" "0")
(command "_insert" "blkuc8" "2560,882.61" "1" "1" "180")
(command "_insert" "blkuc8" "2560,883.35" "1" "1" "0")
(command "_insert" "blkuc8" "2560,882.98" "1" "1" "180")
(command "_insert" "blkuc8" "2560,883.72" "1" "1" "0")
(command "_insert" "blkuc8" "2560,883.35" "1" "1" "180")
(command "_insert" "blkuc8" "2560,884.09" "1" "1" "0")
(command "_insert" "blkuc8" "2560,883.72" "1" "1" "180")
(command "_insert" "blkuc8" "2560,884.46" "1" "1" "0")
(command "_insert" "blkuc8" "2560,884.09" "1" "1" "180")
(command "_insert" "blkuc8" "2560,884.83" "1" "1" "0")
(command "_insert" "blkuc8" "2560,884.46" "1" "1" "180")
(command "_insert" "blkuc8" "2560,885.2" "1" "1" "0")
(command "_insert" "blkuc8" "2560,884.83" "1" "1" "180")
(command "_insert" "blkuc8" "2560,885.57" "1" "1" "0")
(command "_insert" "blkuc8" "2560,885.2" "1" "1" "180")
(command "_insert" "blkuc8" "2560,885.94" "1" "1" "0")
(command "_insert" "blkuc8" "2560,885.57" "1" "1" "180")
(command "_insert" "blkuc8" "2560,886.31" "1" "1" "0")
(command "_insert" "blkuc8" "2560,885.94" "1" "1" "180")
(command "_insert" "blkuc8" "2560,886.68" "1" "1" "0")
(command "_insert" "blkuc8" "2560,886.31" "1" "1" "180")
(command "_insert" "blkuc8" "2560,887.05" "1" "1" "0")
(command "_insert" "blkuc8" "2560,886.68" "1" "1" "180")
(command "_insert" "blkuc8" "2560,887.42" "1" "1" "0")
(command "_insert" "blkuc8" "2560,887.05" "1" "1" "180")
(command "_insert" "blkuc8" "2560,887.79" "1" "1" "0")
(command "_insert" "blkuc8" "2560,887.42" "1" "1" "180")
(command "_insert" "blkuc8" "2560,888.16" "1" "1" "0")
(command "_insert" "blkuc8" "2560,887.79" "1" "1" "180")
(command "_insert" "blkuc8" "2560,888.53" "1" "1" "0")
(command "_insert" "blkuc8" "2560,888.16" "1" "1" "180")
(command "_insert" "blkuc8" "2560,888.9" "1" "1" "0")
(command "_insert" "blkuc8" "2560,888.53" "1" "1" "180")
(command "_insert" "blkuc8" "2560,889.27" "1" "1" "0")
(command "_insert" "blkuc8" "2560,888.9" "1" "1" "180")
(command "_insert" "blkuc8" "2560,889.64" "1" "1" "0")
(command "_insert" "blkuc8" "2560,889.27" "1" "1" "180")
(command "_insert" "blkuc8" "2560,890.01" "1" "1" "0")
(command "_insert" "blkuc8" "2560,889.64" "1" "1" "180")
(command "_insert" "blkuc8" "2560,890.38" "1" "1" "0")
(command "_insert" "blkuc8" "2560,890.01" "1" "1" "180")
(command "_insert" "blkuc8" "2560,890.75" "1" "1" "0")
(command "_insert" "blkuc8" "2560,890.38" "1" "1" "180")
(command "_insert" "blkuc8" "2560,891.12" "1" "1" "0")
(command "_insert" "blkuc8" "2560,890.75" "1" "1" "180")
(command "_insert" "blkuc8" "2560,891.49" "1" "1" "0")
(command "_insert" "blkuc8" "2560,891.12" "1" "1" "180")
(command "_insert" "blkuc8" "2560,891.86" "1" "1" "0")
(command "_insert" "blkuc8" "2560,891.49" "1" "1" "180")
(command "_insert" "blkuc8" "2560,892.23" "1" "1" "0")
(command "_insert" "blkuc8" "2560,891.86" "1" "1" "180")
(command "_insert" "blkuc8" "2560,892.6" "1" "1" "0")
(command "_insert" "blkuc8" "2560,892.23" "1" "1" "180")
(command "_insert" "blkuc8" "2560,892.97" "1" "1" "0")
(command "_insert" "blkuc8" "2560,892.6" "1" "1" "180")
(command "_insert" "blkuc8" "2560,893.34" "1" "1" "0")
(command "_insert" "blkuc8" "2560,892.97" "1" "1" "180")
(command "_insert" "blkuc8" "2560,893.71" "1" "1" "0")
(command "_insert" "blkuc8" "2560,893.34" "1" "1" "180")
(command "_insert" "blkuc8" "2560,894.08" "1" "1" "0")
(command "_insert" "blkuc8" "2560,893.71" "1" "1" "180")
(command "_insert" "blkuc8" "2560,894.45" "1" "1" "0")
(command "_insert" "blkuc8" "2560,894.08" "1" "1" "180")
(command "_insert" "blkuc8" "2560,894.82" "1" "1" "0")
(command "_insert" "blkuc8" "2560,894.45" "1" "1" "180")
(command "_insert" "blkuc8" "2560,895.19" "1" "1" "0")
(command "_insert" "blkuc8" "2560,894.82" "1" "1" "180")
(command "_insert" "blkuc8" "2560,895.56" "1" "1" "0")
(command "_insert" "blkuc8" "2560,895.19" "1" "1" "180")
(command "_insert" "blkuc8" "2560,895.93" "1" "1" "0")
(command "_insert" "blkuc8" "2560,895.56" "1" "1" "180")
(command "_insert" "blkuc8" "2560,896.3" "1" "1" "0")
(command "_insert" "blkuc8" "2560,895.93" "1" "1" "180")
(command "_insert" "blkuc8" "2560,896.67" "1" "1" "0")
(command "_insert" "blkuc8" "2560,896.3" "1" "1" "180")
(command "_insert" "blkuc8" "2560,897.04" "1" "1" "0")
(command "_insert" "blkuc8" "2560,896.67" "1" "1" "180")
(command "_insert" "blkuc8" "2560,897.41" "1" "1" "0")
(command "_insert" "blkuc8" "2560,897.04" "1" "1" "180")
(command "_insert" "blkuc8" "2560,897.78" "1" "1" "0")
(command "_insert" "blkuc8" "2560,897.41" "1" "1" "180")
(command "_insert" "blkuc8" "2560,898.15" "1" "1" "0")
(command "_insert" "blkuc8" "2560,897.78" "1" "1" "180")
(command "_insert" "blkuc8" "2560,898.52" "1" "1" "0")
(command "_insert" "blkuc8" "2560,898.15" "1" "1" "180")
(command "_insert" "blkuc8" "2560,898.89" "1" "1" "0")
(command "_insert" "blkuc8" "2560,898.52" "1" "1" "180")
(command "_insert" "blkuc8" "2560,899.26" "1" "1" "0")
(command "_insert" "blkuc8" "2560,898.89" "1" "1" "180")
(command "_insert" "blkuc8" "2560,899.63" "1" "1" "0")
(command "_insert" "blkuc8" "2560,899.26" "1" "1" "180")
(command "_insert" "blkuc8" "2560,900" "1" "1" "0")
(command "_insert" "blkuc8" "2560,899.63" "1" "1" "180")
(command "_insert" "blkuc8" "2560,900.37" "1" "1" "0")
(command "_insert" "blkuc8" "2560,900" "1" "1" "180")
(command "_insert" "blkuc8" "2560,900.74" "1" "1" "0")
(command "_insert" "blkuc8" "2560,900.37" "1" "1" "180")
(command "_insert" "blkuc8" "2560,901.11" "1" "1" "0")
(command "_insert" "blkuc8" "2560,900.74" "1" "1" "180")
(command "_insert" "blkuc8" "2560,901.48" "1" "1" "0")
(command "_insert" "blkuc8" "2560,901.11" "1" "1" "180")
(command "_insert" "blkuc8" "2560,901.85" "1" "1" "0")
(command "_insert" "blkuc8" "2560,901.48" "1" "1" "180")
(command "_insert" "blkuc8" "2560,902.22" "1" "1" "0")
(command "_insert" "blkuc8" "2560,901.85" "1" "1" "180")
(command "_insert" "blkuc8" "2560,902.59" "1" "1" "0")
(command "_insert" "blkuc8" "2560,902.22" "1" "1" "180")
(command "_insert" "blkuc8" "2560,902.96" "1" "1" "0")
(command "_insert" "blkuc8" "2560,902.59" "1" "1" "180")
(command "_insert" "blkuc8" "2560,903.33" "1" "1" "0")
(command "_insert" "blkuc8" "2560,902.96" "1" "1" "180")
(command "_insert" "blkuc8" "2560,903.7" "1" "1" "0")
(command "_insert" "blkuc8" "2560,903.33" "1" "1" "180")
(command "_insert" "blkuc8" "2560,904.07" "1" "1" "0")
(command "_insert" "blkuc8" "2560,903.7" "1" "1" "180")
(command "_insert" "blkuc8" "2560,904.44" "1" "1" "0")
(command "_insert" "blkuc8" "2560,904.07" "1" "1" "180")
(command "_insert" "blkuc8" "2560,904.81" "1" "1" "0")
(command "_insert" "blkuc8" "2560,904.44" "1" "1" "180")
(command "_insert" "blkuc8" "2560,905.18" "1" "1" "0")
(command "_insert" "blkuc8" "2560,904.81" "1" "1" "180")
(command "_insert" "blkuc8" "2560,905.55" "1" "1" "0")
(command "_insert" "blkuc8" "2560,905.18" "1" "1" "180")
(command "_insert" "blkuc8" "2560,905.92" "1" "1" "0")
(command "_insert" "blkuc8" "2560,905.55" "1" "1" "180")
(command "_insert" "blkuc8" "2560,906.29" "1" "1" "0")
(command "_insert" "blkuc8" "2560,905.92" "1" "1" "180")
(command "_insert" "blkuc8" "2560,906.66" "1" "1" "0")
(command "_insert" "blkuc8" "2560,906.29" "1" "1" "180")
(command "_insert" "blkuc8" "2560,907.03" "1" "1" "0")
(command "_insert" "blkuc8" "2560,906.66" "1" "1" "180")
(command "_insert" "blkuc8" "2560,907.4" "1" "1" "0")
(command "_insert" "blkuc8" "2560,907.03" "1" "1" "180")
(command "_insert" "blkuc8" "2560,907.77" "1" "1" "0")
(command "_insert" "blkuc8" "2560,907.4" "1" "1" "180")
(command "_insert" "blkuc8" "2560,908.14" "1" "1" "0")
(command "_insert" "blkuc8" "2560,907.77" "1" "1" "180")
(command "_insert" "blkuc8" "2560,908.51" "1" "1" "0")
(command "_insert" "blkuc8" "2560,908.14" "1" "1" "180")
(command "_insert" "blkuc8" "2560,908.88" "1" "1" "0")
(command "_insert" "blkuc8" "2560,908.51" "1" "1" "180")
(command "_insert" "blkuc8" "2560,909.25" "1" "1" "0")
(command "_insert" "blkuc8" "2560,908.88" "1" "1" "180")
(command "_insert" "blkuc8" "2560,909.62" "1" "1" "0")
(command "_insert" "blkuc8" "2560,909.25" "1" "1" "180")
(command "_insert" "blkuc8" "2560,909.99" "1" "1" "0")
(command "_insert" "blkuc8" "2560,909.62" "1" "1" "180")
(command "_insert" "blkuc8" "2560,910.36" "1" "1" "0")
(command "_insert" "blkuc8" "2560,909.99" "1" "1" "180")
(command "_insert" "blkuc8" "2560,910.73" "1" "1" "0")
(command "_insert" "blkuc8" "2560,910.36" "1" "1" "180")
(command "_insert" "blkuc8" "2560,911.1" "1" "1" "0")
(command "_insert" "blkuc8" "2560,910.73" "1" "1" "180")
(command "_insert" "blkuc8" "2560,911.47" "1" "1" "0")
(command "_insert" "blkuc8" "2560,911.1" "1" "1" "180")
(command "_insert" "blkuc8" "2560,911.84" "1" "1" "0")
(command "_insert" "blkuc8" "2560,911.47" "1" "1" "180")
(command "_insert" "blkuc8" "2560,912.21" "1" "1" "0")
(command "_insert" "blkuc8" "2560,911.84" "1" "1" "180")
(command "_insert" "blkuc8" "2560,912.58" "1" "1" "0")
(command "_insert" "blkuc8" "2560,912.21" "1" "1" "180")
(command "_insert" "blkuc8" "2560,912.95" "1" "1" "0")
(command "_insert" "blkuc8" "2560,912.58" "1" "1" "180")
(command "_insert" "blkuc8" "2560,913.32" "1" "1" "0")
(command "_insert" "blkuc8" "2560,912.95" "1" "1" "180")
(command "_insert" "blkuc8" "2560,913.69" "1" "1" "0")
(command "_insert" "blkuc8" "2560,913.32" "1" "1" "180")
(command "_insert" "blkuc8" "2560,914.06" "1" "1" "0")
(command "_insert" "blkuc8" "2560,913.69" "1" "1" "180")
(command "_insert" "blkuc8" "2560,914.43" "1" "1" "0")
(command "_insert" "blkuc8" "2560,914.06" "1" "1" "180")
(command "_insert" "blkuc8" "2560,914.8" "1" "1" "0")
(command "_insert" "blkuc8" "2560,914.43" "1" "1" "180")
(command "_insert" "blkuc8" "2560,915.17" "1" "1" "0")
(command "_insert" "blkuc8" "2560,914.8" "1" "1" "180")
(command "_insert" "blkuc8" "2560,915.54" "1" "1" "0")
(command "_insert" "blkuc8" "2560,915.17" "1" "1" "180")
(command "_insert" "blkuc8" "2560,915.91" "1" "1" "0")
(command "_insert" "blkuc8" "2560,915.54" "1" "1" "180")
(command "_insert" "blkuc8" "2560,916.28" "1" "1" "0")
(command "_insert" "blkuc8" "2560,915.91" "1" "1" "180")
(command "_insert" "blkuc8" "2560,916.65" "1" "1" "0")
(command "_insert" "blkuc8" "2560,916.28" "1" "1" "180")
(command "_insert" "blkuc8" "2560,917.02" "1" "1" "0")
(command "_insert" "blkuc8" "2560,916.65" "1" "1" "180")
(command "_insert" "blkuc8" "2560,917.39" "1" "1" "0")
(command "_insert" "blkuc8" "2560,917.02" "1" "1" "180")
(command "_insert" "blkuc8" "2560,917.76" "1" "1" "0")
(command "_insert" "blkuc8" "2560,917.39" "1" "1" "180")
(command "_insert" "blkuc8" "2560,918.13" "1" "1" "0")
(command "_insert" "blkuc8" "2560,917.76" "1" "1" "180")
(command "_insert" "blkuc8" "2560,918.5" "1" "1" "0")
(command "_insert" "blkuc8" "2560,918.13" "1" "1" "180")
(command "_insert" "blkuc8" "2560,918.87" "1" "1" "0")
(command "_insert" "blkuc8" "2560,918.5" "1" "1" "180")
(command "_insert" "blkuc8" "2560,919.24" "1" "1" "0")
(command "_insert" "blkuc8" "2560,918.87" "1" "1" "180")
(command "_insert" "blkuc8" "2560,919.61" "1" "1" "0")
(command "_insert" "blkuc8" "2560,919.24" "1" "1" "180")
(command "_insert" "blkuc8" "2560,919.98" "1" "1" "0")
(command "_insert" "blkuc8" "2560,919.61" "1" "1" "180")
(command "_insert" "blkuc8" "2560,920.35" "1" "1" "0")
(command "_insert" "blkuc8" "2560,919.98" "1" "1" "180")
(command "_insert" "blkuc8" "2560,920.72" "1" "1" "0")
(command "_insert" "blkuc8" "2560,920.35" "1" "1" "180")
(command "_insert" "blkuc8" "2560,921.09" "1" "1" "0")
(command "_insert" "blkuc8" "2560,920.72" "1" "1" "180")
(command "_insert" "blkuc8" "2560,921.46" "1" "1" "0")
(command "_insert" "blkuc8" "2560,921.09" "1" "1" "180")
(command "_insert" "blkuc8" "2560,921.83" "1" "1" "0")
(command "_insert" "blkuc8" "2560,921.46" "1" "1" "180")
(command "_insert" "blkuc8" "2560,922.2" "1" "1" "0")
(command "_insert" "blkuc8" "2560,921.83" "1" "1" "180")
(command "_insert" "blkuc8" "2560,922.57" "1" "1" "0")
(command "_insert" "blkuc8" "2560,922.2" "1" "1" "180")
(command "_insert" "blkuc8" "2560,922.94" "1" "1" "0")
(command "_insert" "blkuc8" "2560,922.57" "1" "1" "180")
(command "_insert" "blkuc8" "2560,923.31" "1" "1" "0")
(command "_insert" "blkuc8" "2560,922.94" "1" "1" "180")
(command "_insert" "blkuc8" "2560,923.68" "1" "1" "0")
(command "_insert" "blkuc8" "2560,923.31" "1" "1" "180")
(command "_insert" "blkuc8" "2560,924.05" "1" "1" "0")
(command "_insert" "blkuc8" "2560,923.68" "1" "1" "180")
(command "_insert" "blkuc8" "2560,924.42" "1" "1" "0")
(command "_insert" "blkuc8" "2560,924.05" "1" "1" "180")
(command "_insert" "blkuc8" "2560,924.79" "1" "1" "0")
(command "_insert" "blkuc8" "2560,924.42" "1" "1" "180")
(command "_insert" "blkuc8" "2560,925.16" "1" "1" "0")
(command "_insert" "blkuc8" "2560,924.79" "1" "1" "180")
(command "_insert" "blkuc8" "2560,925.53" "1" "1" "0")
(command "_insert" "blkuc8" "2560,925.16" "1" "1" "180")
(command "_insert" "blkuc8" "2560,925.9" "1" "1" "0")
(command "_insert" "blkuc8" "2560,925.53" "1" "1" "180")
(command "_insert" "blkuc8" "2560,926.27" "1" "1" "0")
(command "_insert" "blkuc8" "2560,925.9" "1" "1" "180")
(command "_insert" "blkuc8" "2560,926.64" "1" "1" "0")
(command "_insert" "blkuc8" "2560,926.27" "1" "1" "180")
(command "_insert" "blkuc8" "2560,927.01" "1" "1" "0")
(command "_insert" "blkuc8" "2560,926.64" "1" "1" "180")
(command "_insert" "blkuc8" "2560,927.38" "1" "1" "0")
(command "_insert" "blkuc8" "2560,927.01" "1" "1" "180")
(command "_insert" "blkuc8" "2560,927.75" "1" "1" "0")
(command "_insert" "blkuc8" "2560,927.38" "1" "1" "180")
(command "_layer" "set" "phccover" "")
(command "_rectangle" "2558.878,933.3" "2561.122,866.7")
(command "_layer" "set" "nitride" "")
(setq phc8 currobj)
(command "_layer" "set" "cover" "")
(command "_rectangle" "2558.878,836.7" "2561.122,963.3")
(command "_layer" "set" "nitride" "")
(command "_layer" "set" "text" "")
(command "_circle" "2557.928,846.7" "0.075")
(command "_circle" "2557.553,846.7" "0.15")
(command "_circle" "2557.178,846.7" "0.075")
(command "_circle" "2556.803,846.7" "0.15")
(command "_circle" "2557.928,848.7" "0.075")
(command "_circle" "2557.553,848.7" "0.075")
(command "_circle" "2557.178,848.7" "0.15")
(command "_circle" "2556.803,848.7" "0.15")
(command "_circle" "2557.928,850.7" "0.075")
(command "_circle" "2557.553,850.7" "0.15")
(command "_circle" "2557.178,850.7" "0.15")
(command "_circle" "2556.803,850.7" "0.15")
(command "_circle" "2557.928,852.7" "0.075")
(command "_circle" "2557.553,852.7" "0.075")
(command "_circle" "2557.178,852.7" "0.075")
(command "_circle" "2556.803,852.7" "0.075")
(command "_circle" "2556.428,852.7" "0.15")
(command "_circle" "2557.928,854.7" "0.075")
(command "_circle" "2557.553,854.7" "0.15")
(command "_circle" "2557.178,854.7" "0.075")
(command "_circle" "2556.803,854.7" "0.075")
(command "_circle" "2556.428,854.7" "0.15")
(command "_circle" "2557.928,856.7" "0.075")
(command "_circle" "2557.553,856.7" "0.075")
(command "_circle" "2557.178,856.7" "0.15")
(command "_circle" "2556.803,856.7" "0.075")
(command "_circle" "2556.428,856.7" "0.15")
(command "_circle" "2557.928,858.7" "0.075")
(command "_circle" "2557.553,858.7" "0.15")
(command "_circle" "2557.178,858.7" "0.15")
(command "_circle" "2556.803,858.7" "0.075")
(command "_circle" "2556.428,858.7" "0.15")
(command "_circle" "2557.928,860.7" "0.075")
(command "_circle" "2557.553,860.7" "0.075")
(command "_circle" "2557.178,860.7" "0.075")
(command "_circle" "2556.803,860.7" "0.15")
(command "_circle" "2556.428,860.7" "0.15")
(command "_circle" "2557.928,862.7" "0.075")
(command "_circle" "2557.553,862.7" "0.15")
(command "_circle" "2557.178,862.7" "0.075")
(command "_circle" "2556.803,862.7" "0.15")
(command "_circle" "2556.428,862.7" "0.15")
(command "_circle" "2557.928,864.7" "0.075")
(command "_circle" "2557.553,864.7" "0.075")
(command "_circle" "2557.178,864.7" "0.15")
(command "_circle" "2556.803,864.7" "0.15")
(command "_circle" "2556.428,864.7" "0.15")
(command "_circle" "2557.928,866.7" "0.075")
(command "_circle" "2557.553,866.7" "0.15")
(command "_circle" "2557.178,866.7" "0.15")
(command "_circle" "2556.803,866.7" "0.15")
(command "_circle" "2556.428,866.7" "0.15")
(command "_circle" "2557.928,868.7" "0.075")
(command "_circle" "2557.553,868.7" "0.075")
(command "_circle" "2557.178,868.7" "0.075")
(command "_circle" "2556.803,868.7" "0.075")
(command "_circle" "2556.428,868.7" "0.075")
(command "_circle" "2556.053,868.7" "0.15")
(command "_circle" "2557.928,870.7" "0.075")
(command "_circle" "2557.553,870.7" "0.15")
(command "_circle" "2557.178,870.7" "0.075")
(command "_circle" "2556.803,870.7" "0.075")
(command "_circle" "2556.428,870.7" "0.075")
(command "_circle" "2556.053,870.7" "0.15")
(command "_circle" "2557.928,872.7" "0.075")
(command "_circle" "2557.553,872.7" "0.075")
(command "_circle" "2557.178,872.7" "0.15")
(command "_circle" "2556.803,872.7" "0.075")
(command "_circle" "2556.428,872.7" "0.075")
(command "_circle" "2556.053,872.7" "0.15")
(command "_circle" "2557.928,874.7" "0.075")
(command "_circle" "2557.553,874.7" "0.15")
(command "_circle" "2557.178,874.7" "0.15")
(command "_circle" "2556.803,874.7" "0.075")
(command "_circle" "2556.428,874.7" "0.075")
(command "_circle" "2556.053,874.7" "0.15")
(command "_circle" "2557.928,876.7" "0.075")
(command "_circle" "2557.553,876.7" "0.075")
(command "_circle" "2557.178,876.7" "0.075")
(command "_circle" "2556.803,876.7" "0.15")
(command "_circle" "2556.428,876.7" "0.075")
(command "_circle" "2556.053,876.7" "0.15")
(command "_circle" "2557.928,878.7" "0.075")
(command "_circle" "2557.553,878.7" "0.15")
(command "_circle" "2557.178,878.7" "0.075")
(command "_circle" "2556.803,878.7" "0.15")
(command "_circle" "2556.428,878.7" "0.075")
(command "_circle" "2556.053,878.7" "0.15")
(command "_circle" "2557.928,880.7" "0.075")
(command "_circle" "2557.553,880.7" "0.075")
(command "_circle" "2557.178,880.7" "0.15")
(command "_circle" "2556.803,880.7" "0.15")
(command "_circle" "2556.428,880.7" "0.075")
(command "_circle" "2556.053,880.7" "0.15")
(command "_circle" "2557.928,882.7" "0.075")
(command "_circle" "2557.553,882.7" "0.15")
(command "_circle" "2557.178,882.7" "0.15")
(command "_circle" "2556.803,882.7" "0.15")
(command "_circle" "2556.428,882.7" "0.075")
(command "_circle" "2556.053,882.7" "0.15")
(command "_circle" "2557.928,884.7" "0.075")
(command "_circle" "2557.553,884.7" "0.075")
(command "_circle" "2557.178,884.7" "0.075")
(command "_circle" "2556.803,884.7" "0.075")
(command "_circle" "2556.428,884.7" "0.15")
(command "_circle" "2556.053,884.7" "0.15")
(command "_circle" "2557.928,886.7" "0.075")
(command "_circle" "2557.553,886.7" "0.15")
(command "_circle" "2557.178,886.7" "0.075")
(command "_circle" "2556.803,886.7" "0.075")
(command "_circle" "2556.428,886.7" "0.15")
(command "_circle" "2556.053,886.7" "0.15")
(command "_circle" "2557.928,888.7" "0.075")
(command "_circle" "2557.553,888.7" "0.075")
(command "_circle" "2557.178,888.7" "0.15")
(command "_circle" "2556.803,888.7" "0.075")
(command "_circle" "2556.428,888.7" "0.15")
(command "_circle" "2556.053,888.7" "0.15")
(command "_circle" "2557.928,890.7" "0.075")
(command "_circle" "2557.553,890.7" "0.15")
(command "_circle" "2557.178,890.7" "0.15")
(command "_circle" "2556.803,890.7" "0.075")
(command "_circle" "2556.428,890.7" "0.15")
(command "_circle" "2556.053,890.7" "0.15")
(command "_circle" "2557.928,892.7" "0.075")
(command "_circle" "2557.553,892.7" "0.075")
(command "_circle" "2557.178,892.7" "0.075")
(command "_circle" "2556.803,892.7" "0.15")
(command "_circle" "2556.428,892.7" "0.15")
(command "_circle" "2556.053,892.7" "0.15")
(command "_circle" "2557.928,894.7" "0.075")
(command "_circle" "2557.553,894.7" "0.15")
(command "_circle" "2557.178,894.7" "0.075")
(command "_circle" "2556.803,894.7" "0.15")
(command "_circle" "2556.428,894.7" "0.15")
(command "_circle" "2556.053,894.7" "0.15")
(command "_circle" "2557.928,896.7" "0.075")
(command "_circle" "2557.553,896.7" "0.075")
(command "_circle" "2557.178,896.7" "0.15")
(command "_circle" "2556.803,896.7" "0.15")
(command "_circle" "2556.428,896.7" "0.15")
(command "_circle" "2556.053,896.7" "0.15")
(command "_circle" "2557.928,898.7" "0.075")
(command "_circle" "2557.553,898.7" "0.15")
(command "_circle" "2557.178,898.7" "0.15")
(command "_circle" "2556.803,898.7" "0.15")
(command "_circle" "2556.428,898.7" "0.15")
(command "_circle" "2556.053,898.7" "0.15")
(command "_circle" "2557.928,900.7" "0.075")
(command "_circle" "2557.553,900.7" "0.075")
(command "_circle" "2557.178,900.7" "0.075")
(command "_circle" "2556.803,900.7" "0.075")
(command "_circle" "2556.428,900.7" "0.075")
(command "_circle" "2556.053,900.7" "0.075")
(command "_circle" "2555.678,900.7" "0.15")
(command "_circle" "2557.928,902.7" "0.075")
(command "_circle" "2557.553,902.7" "0.15")
(command "_circle" "2557.178,902.7" "0.075")
(command "_circle" "2556.803,902.7" "0.075")
(command "_circle" "2556.428,902.7" "0.075")
(command "_circle" "2556.053,902.7" "0.075")
(command "_circle" "2555.678,902.7" "0.15")
(command "_circle" "2557.928,904.7" "0.075")
(command "_circle" "2557.553,904.7" "0.075")
(command "_circle" "2557.178,904.7" "0.15")
(command "_circle" "2556.803,904.7" "0.075")
(command "_circle" "2556.428,904.7" "0.075")
(command "_circle" "2556.053,904.7" "0.075")
(command "_circle" "2555.678,904.7" "0.15")
(command "_circle" "2557.928,906.7" "0.075")
(command "_circle" "2557.553,906.7" "0.15")
(command "_circle" "2557.178,906.7" "0.15")
(command "_circle" "2556.803,906.7" "0.075")
(command "_circle" "2556.428,906.7" "0.075")
(command "_circle" "2556.053,906.7" "0.075")
(command "_circle" "2555.678,906.7" "0.15")
(command "_circle" "2557.928,908.7" "0.075")
(command "_circle" "2557.553,908.7" "0.075")
(command "_circle" "2557.178,908.7" "0.075")
(command "_circle" "2556.803,908.7" "0.15")
(command "_circle" "2556.428,908.7" "0.075")
(command "_circle" "2556.053,908.7" "0.075")
(command "_circle" "2555.678,908.7" "0.15")
(command "_circle" "2557.928,910.7" "0.075")
(command "_circle" "2557.553,910.7" "0.15")
(command "_circle" "2557.178,910.7" "0.075")
(command "_circle" "2556.803,910.7" "0.15")
(command "_circle" "2556.428,910.7" "0.075")
(command "_circle" "2556.053,910.7" "0.075")
(command "_circle" "2555.678,910.7" "0.15")
(command "_circle" "2557.928,912.7" "0.075")
(command "_circle" "2557.553,912.7" "0.075")
(command "_circle" "2557.178,912.7" "0.15")
(command "_circle" "2556.803,912.7" "0.15")
(command "_circle" "2556.428,912.7" "0.075")
(command "_circle" "2556.053,912.7" "0.075")
(command "_circle" "2555.678,912.7" "0.15")
(command "_circle" "2557.928,914.7" "0.075")
(command "_circle" "2557.553,914.7" "0.15")
(command "_circle" "2557.178,914.7" "0.15")
(command "_circle" "2556.803,914.7" "0.15")
(command "_circle" "2556.428,914.7" "0.075")
(command "_circle" "2556.053,914.7" "0.075")
(command "_circle" "2555.678,914.7" "0.15")
(command "_circle" "2557.928,916.7" "0.075")
(command "_circle" "2557.553,916.7" "0.075")
(command "_circle" "2557.178,916.7" "0.075")
(command "_circle" "2556.803,916.7" "0.075")
(command "_circle" "2556.428,916.7" "0.15")
(command "_circle" "2556.053,916.7" "0.075")
(command "_circle" "2555.678,916.7" "0.15")
(command "_circle" "2557.928,918.7" "0.075")
(command "_circle" "2557.553,918.7" "0.15")
(command "_circle" "2557.178,918.7" "0.075")
(command "_circle" "2556.803,918.7" "0.075")
(command "_circle" "2556.428,918.7" "0.15")
(command "_circle" "2556.053,918.7" "0.075")
(command "_circle" "2555.678,918.7" "0.15")
(command "_circle" "2557.928,920.7" "0.075")
(command "_circle" "2557.553,920.7" "0.075")
(command "_circle" "2557.178,920.7" "0.15")
(command "_circle" "2556.803,920.7" "0.075")
(command "_circle" "2556.428,920.7" "0.15")
(command "_circle" "2556.053,920.7" "0.075")
(command "_circle" "2555.678,920.7" "0.15")
(command "_circle" "2557.928,922.7" "0.075")
(command "_circle" "2557.553,922.7" "0.15")
(command "_circle" "2557.178,922.7" "0.15")
(command "_circle" "2556.803,922.7" "0.075")
(command "_circle" "2556.428,922.7" "0.15")
(command "_circle" "2556.053,922.7" "0.075")
(command "_circle" "2555.678,922.7" "0.15")
(command "_circle" "2557.928,924.7" "0.075")
(command "_circle" "2557.553,924.7" "0.075")
(command "_circle" "2557.178,924.7" "0.075")
(command "_circle" "2556.803,924.7" "0.15")
(command "_circle" "2556.428,924.7" "0.15")
(command "_circle" "2556.053,924.7" "0.075")
(command "_circle" "2555.678,924.7" "0.15")
(command "_circle" "2557.928,926.7" "0.075")
(command "_circle" "2557.553,926.7" "0.15")
(command "_circle" "2557.178,926.7" "0.075")
(command "_circle" "2556.803,926.7" "0.15")
(command "_circle" "2556.428,926.7" "0.15")
(command "_circle" "2556.053,926.7" "0.075")
(command "_circle" "2555.678,926.7" "0.15")
(command "_circle" "2557.928,928.7" "0.075")
(command "_circle" "2557.553,928.7" "0.075")
(command "_circle" "2557.178,928.7" "0.15")
(command "_circle" "2556.803,928.7" "0.15")
(command "_circle" "2556.428,928.7" "0.15")
(command "_circle" "2556.053,928.7" "0.075")
(command "_circle" "2555.678,928.7" "0.15")
(command "_circle" "2557.928,930.7" "0.075")
(command "_circle" "2557.553,930.7" "0.15")
(command "_circle" "2557.178,930.7" "0.15")
(command "_circle" "2556.803,930.7" "0.15")
(command "_circle" "2556.428,930.7" "0.15")
(command "_circle" "2556.053,930.7" "0.075")
(command "_circle" "2555.678,930.7" "0.15")
(command "_circle" "2557.928,932.7" "0.075")
(command "_circle" "2557.553,932.7" "0.075")
(command "_circle" "2557.178,932.7" "0.075")
(command "_circle" "2556.803,932.7" "0.075")
(command "_circle" "2556.428,932.7" "0.075")
(command "_circle" "2556.053,932.7" "0.15")
(command "_circle" "2555.678,932.7" "0.15")
(command "_circle" "2557.928,934.7" "0.075")
(command "_circle" "2557.553,934.7" "0.15")
(command "_circle" "2557.178,934.7" "0.075")
(command "_circle" "2556.803,934.7" "0.075")
(command "_circle" "2556.428,934.7" "0.075")
(command "_circle" "2556.053,934.7" "0.15")
(command "_circle" "2555.678,934.7" "0.15")
(command "_circle" "2557.928,936.7" "0.075")
(command "_circle" "2557.553,936.7" "0.075")
(command "_circle" "2557.178,936.7" "0.15")
(command "_circle" "2556.803,936.7" "0.075")
(command "_circle" "2556.428,936.7" "0.075")
(command "_circle" "2556.053,936.7" "0.15")
(command "_circle" "2555.678,936.7" "0.15")
(command "_circle" "2557.928,938.7" "0.075")
(command "_circle" "2557.553,938.7" "0.15")
(command "_circle" "2557.178,938.7" "0.15")
(command "_circle" "2556.803,938.7" "0.075")
(command "_circle" "2556.428,938.7" "0.075")
(command "_circle" "2556.053,938.7" "0.15")
(command "_circle" "2555.678,938.7" "0.15")
(command "_circle" "2557.928,940.7" "0.075")
(command "_circle" "2557.553,940.7" "0.075")
(command "_circle" "2557.178,940.7" "0.075")
(command "_circle" "2556.803,940.7" "0.15")
(command "_circle" "2556.428,940.7" "0.075")
(command "_circle" "2556.053,940.7" "0.15")
(command "_circle" "2555.678,940.7" "0.15")
(command "_circle" "2557.928,942.7" "0.075")
(command "_circle" "2557.553,942.7" "0.15")
(command "_circle" "2557.178,942.7" "0.075")
(command "_circle" "2556.803,942.7" "0.15")
(command "_circle" "2556.428,942.7" "0.075")
(command "_circle" "2556.053,942.7" "0.15")
(command "_circle" "2555.678,942.7" "0.15")
(command "_circle" "2557.928,944.7" "0.075")
(command "_circle" "2557.553,944.7" "0.075")
(command "_circle" "2557.178,944.7" "0.15")
(command "_circle" "2556.803,944.7" "0.15")
(command "_circle" "2556.428,944.7" "0.075")
(command "_circle" "2556.053,944.7" "0.15")
(command "_circle" "2555.678,944.7" "0.15")
(command "_circle" "2557.928,946.7" "0.075")
(command "_circle" "2557.553,946.7" "0.15")
(command "_circle" "2557.178,946.7" "0.15")
(command "_circle" "2556.803,946.7" "0.15")
(command "_circle" "2556.428,946.7" "0.075")
(command "_circle" "2556.053,946.7" "0.15")
(command "_circle" "2555.678,946.7" "0.15")
(command "_circle" "2557.928,948.7" "0.075")
(command "_circle" "2557.553,948.7" "0.075")
(command "_circle" "2557.178,948.7" "0.075")
(command "_circle" "2556.803,948.7" "0.075")
(command "_circle" "2556.428,948.7" "0.15")
(command "_circle" "2556.053,948.7" "0.15")
(command "_circle" "2555.678,948.7" "0.15")
(command "_circle" "2557.928,950.7" "0.075")
(command "_circle" "2557.553,950.7" "0.15")
(command "_circle" "2557.178,950.7" "0.075")
(command "_circle" "2556.803,950.7" "0.075")
(command "_circle" "2556.428,950.7" "0.15")
(command "_circle" "2556.053,950.7" "0.15")
(command "_circle" "2555.678,950.7" "0.15")
(command "_circle" "2557.928,952.7" "0.075")
(command "_circle" "2557.553,952.7" "0.075")
(command "_circle" "2557.178,952.7" "0.15")
(command "_circle" "2556.803,952.7" "0.075")
(command "_circle" "2556.428,952.7" "0.15")
(command "_circle" "2556.053,952.7" "0.15")
(command "_circle" "2555.678,952.7" "0.15")
(command "_circle" "2557.928,954.7" "0.075")
(command "_circle" "2557.553,954.7" "0.15")
(command "_circle" "2557.178,954.7" "0.15")
(command "_circle" "2556.803,954.7" "0.075")
(command "_circle" "2556.428,954.7" "0.15")
(command "_circle" "2556.053,954.7" "0.15")
(command "_circle" "2555.678,954.7" "0.15")
(command "_circle" "2557.928,956.7" "0.075")
(command "_circle" "2557.553,956.7" "0.075")
(command "_circle" "2557.178,956.7" "0.075")
(command "_circle" "2556.803,956.7" "0.15")
(command "_circle" "2556.428,956.7" "0.15")
(command "_circle" "2556.053,956.7" "0.15")
(command "_circle" "2555.678,956.7" "0.15")
(command "_circle" "2557.928,958.7" "0.075")
(command "_circle" "2557.553,958.7" "0.15")
(command "_circle" "2557.178,958.7" "0.075")
(command "_circle" "2556.803,958.7" "0.15")
(command "_circle" "2556.428,958.7" "0.15")
(command "_circle" "2556.053,958.7" "0.15")
(command "_circle" "2555.678,958.7" "0.15")
(command "_circle" "2557.928,960.7" "0.075")
(command "_circle" "2557.553,960.7" "0.075")
(command "_circle" "2557.178,960.7" "0.15")
(command "_circle" "2556.803,960.7" "0.15")
(command "_circle" "2556.428,960.7" "0.15")
(command "_circle" "2556.053,960.7" "0.15")
(command "_circle" "2555.678,960.7" "0.15")
(command "_circle" "2557.928,962.7" "0.075")
(command "_circle" "2557.553,962.7" "0.15")
(command "_circle" "2557.178,962.7" "0.15")
(command "_circle" "2556.803,962.7" "0.15")
(command "_circle" "2556.428,962.7" "0.15")
(command "_circle" "2556.053,962.7" "0.15")
(command "_circle" "2555.678,962.7" "0.15")
(command "_layer" "set" "nitride" "")
(command "_layer" "set" "text" "")
(command-s "_text" "2546.878,963.3" "2" "-90" "a = 370 nm" )
(sssetfirst nil (ssget "_L"))
(if (not (numberp (vl-string-search "Mac" (getvar "platform")))) (c:txtexp))
(command "_layer" "set" "nitride" "")
(command "_layer" "set" "text" "")
(command-s "_text" "2543.878,963.3" "2" "-90" "gap = 250 nm" )
(sssetfirst nil (ssget "_L"))
(if (not (numberp (vl-string-search "Mac" (getvar "platform")))) (c:txtexp))
(command "_layer" "set" "nitride" "")
(command "_layer" "set" "text" "")
(command-s "_text" "2540.878,963.3" "2" "-90" "amplitude = 142 nm" )
(sssetfirst nil (ssget "_L"))
(if (not (numberp (vl-string-search "Mac" (getvar "platform")))) (c:txtexp))
(command "_layer" "set" "nitride" "")
(command "_layer" "set" "text" "")
(command-s "_text" "2537.878,963.3" "2" "-90" "start width = 280 nm" )
(sssetfirst nil (ssget "_L"))
(if (not (numberp (vl-string-search "Mac" (getvar "platform")))) (c:txtexp))
(command "_layer" "set" "nitride" "")
(command "_layer" "set" "text" "")
(command-s "_text" "2534.878,963.3" "2" "-90" "width = 294 nm" )
(sssetfirst nil (ssget "_L"))
(if (not (numberp (vl-string-search "Mac" (getvar "platform")))) (c:txtexp))
(command "_layer" "set" "nitride" "")
(command "_layer" "set" "text" "")
(command-s "_text" "2531.878,963.3" "2" "-90" "taper: 15" )
(sssetfirst nil (ssget "_L"))
(if (not (numberp (vl-string-search "Mac" (getvar "platform")))) (c:txtexp))
(command "_layer" "set" "nitride" "")
(command "_layer" "set" "text" "")
(command-s "_text" "2528.878,963.3" "2" "-90" "nominal: 150" )
(sssetfirst nil (ssget "_L"))
(if (not (numberp (vl-string-search "Mac" (getvar "platform")))) (c:txtexp))
(command "_layer" "set" "nitride" "")
(command "_layer" "set" "indicators" "")
(setq coords (list 
(list 2480.415 940) 
(list 2480.415 920) 
(list 2460.415 900) 
(list 2480.415 880) 
(list 2480.415 860) 
(list 2480.415 900) 
(list 2480.415 887.0711) 
(list 2467.4861 900) 
(list 2480.415 912.9289) 
(list 2480.415 900)))
(apply 'command (append '("pline") coords '("c")))
(command "._fillet" "radius" "1" "._fillet" "P" (entlast))
(setq coords (list 
(list 2639.585 940) 
(list 2639.585 920) 
(list 2659.585 900) 
(list 2639.585 880) 
(list 2639.585 860) 
(list 2639.585 900) 
(list 2639.585 887.0711) 
(list 2652.5139 900) 
(list 2639.585 912.9289) 
(list 2639.585 900)))
(apply 'command (append '("pline") coords '("c")))
(command "._fillet" "radius" "1" "._fillet" "P" (entlast))
(command "_layer" "set" "holes" "")
(command "_circle" "2478.0629,914.1124" "0.5")
(command "_circle" "2475.7109,911.7603" "0.5")
(command "_circle" "2473.3588,909.4083" "0.5")
(command "_circle" "2471.0067,907.0562" "0.5")
(command "_circle" "2468.6547,904.7041" "0.5")
(command "_circle" "2466.3026,902.3521" "0.5")
(command "_circle" "2463.9505,900" "0.5")
(command "_circle" "2466.3026,897.6479" "0.5")
(command "_circle" "2468.6547,895.2959" "0.5")
(command "_circle" "2471.0067,892.9438" "0.5")
(command "_circle" "2473.3588,890.5917" "0.5")
(command "_circle" "2475.7109,888.2397" "0.5")
(command "_circle" "2478.0629,885.8876" "0.5")
(command "_circle" "2641.9371,914.1124" "0.5")
(command "_circle" "2644.2891,911.7603" "0.5")
(command "_circle" "2646.6412,909.4083" "0.5")
(command "_circle" "2648.9933,907.0562" "0.5")
(command "_circle" "2651.3453,904.7041" "0.5")
(command "_circle" "2653.6974,902.3521" "0.5")
(command "_circle" "2656.0495,900" "0.5")
(command "_circle" "2653.6974,897.6479" "0.5")
(command "_circle" "2651.3453,895.2959" "0.5")
(command "_circle" "2648.9933,892.9438" "0.5")
(command "_circle" "2646.6412,890.5917" "0.5")
(command "_circle" "2644.2891,888.2397" "0.5")
(command "_circle" "2641.9371,885.8876" "0.5")
(command "_layer" "set" "nitride" "")
(command "_block" "blkcoupler8" "2560,900" coupler8 "")
(command "_insert" "blkcoupler8" "2560,900" "1" "1" "0")
(command "_insert" "blkcoupler8" "2560,900" "1" "1" "180")
(command "_block" "blksinglenanobeam8" "2560,900" singlenanobeam8 "")
(command "_insert" "blksinglenanobeam8" "2560,900" "1" "1" "0")
(command "_insert" "blksinglenanobeam8" "2560,900" "1" "1" "180")
(command "_block" "blkanglednodearray8" "2560,900" anglednodearray8 "")
(command "_insert" "blkanglednodearray8" "2560,900" "1" "1" "0")
(command "_insert" "blkanglednodearray8" "2560,900" "1" "1" "180")
(command "_block" "blkcooledsinglenanobeam8" "2560,900" cooledsinglenanobeam8 "")
(command "_insert" "blkcooledsinglenanobeam8" "2560,900" "1" "1" "0")
(command "_insert" "blkcooledsinglenanobeam8" "2560,900" "1" "1" "180")
(command "_block" "blkyjunction8" "2560,900" yjunction8 "")
(command "_insert" "blkyjunction8" "2560,900" "1" "1" "0")
(command "_insert" "blkyjunction8" "2560,900" "1" "1" "180")
; DRAWING BULGING VEE GROOVE
(command "_layer" "set" "vgroove" "")
(setq coords (list 
(list 2485.415 -605) 
(list 2485.415 0) 
(list 2485.415 0) 
(list 2485.415 1800) 
(list 2485.415 1800) 
(list 2485.415 2405) 
(list 2634.585 2405) 
(list 2634.585 1800) 
(list 2634.585 1800) 
(list 2634.585 0) 
(list 2634.585 0) 
(list 2634.585 -605)))
(apply 'command (append '("pline") coords '("c")))
(command "._fillet" "radius" "0" "._fillet" "P" (entlast))
(command "_layer" "set" "window" "")
(command "_rectangle" "2485.415,-1935" "2634.585,-600")
(command "_rectangle" "2485.415,2400" "2634.585,5300")
(command "_layer" "set" "grid" "")
(command "_rectangle" "2486.415,-1934" "2509.9433,-1909.2133")
(command "_array" "last" "" "R" "75" "3" "25.7867" "24.5283")
(command "_rectangle" "2561,-1934" "2584.5283,-1909.2133")
(command "_array" "last" "" "R" "75" "3" "25.7867" "24.5283")
(command "_rectangle" "2486.415,1" "2509.9433,25.7")
(command "_array" "last" "" "R" "70" "3" "25.7" "24.5283")
(command "_rectangle" "2561,1" "2584.5283,25.7")
(command "_array" "last" "" "R" "70" "3" "25.7" "24.5283")
(command "_rectangle" "2486.415,1801" "2509.9433,1825.9185")
(command "_array" "last" "" "R" "135" "3" "25.9185" "24.5283")
(command "_rectangle" "2561,1801" "2584.5283,1825.9185")
(command "_array" "last" "" "R" "135" "3" "25.9185" "24.5283")
(command "_layer" "set" "vgrooveFDA" "")
(command "_rectangle" "2634.585,-2233" "2485.415,-1933")
(command "_layer" "set" "nitride" "")
(command "_layer" "set" "holes" "")
(command "_circle" "2637.085,331.5" "0.5")
(command "_array" "last" "" "R" "379" "1" "3" "2.5")
(command "_circle" "2482.915,331.5" "0.5")
(command "_array" "last" "" "R" "379" "1" "3" "-2.5")
(command "_layer" "set" "nitride" "")
(command "_layer" "set" "window" "")
(command "_layer" "set" "window" "")
(command "_rectangle" "2639.585,0" "2800.415,1800")
(command "._fillet" "radius" "20" "._fillet" "P" (entlast))
(command "_layer" "set" "grid" "")
(command "_rectangle" "2640.585,1" "2662.4179,25.7")
(command "_array" "last" "" "R" "70" "7" "25.7" "22.8329")
(command "_layer" "set" "nitride" "")
; DRAWING REGION LAYER
(command "_layer" "set" "regionLayer8" "")
(command "_rectangle" "2480,-460" "2640,2260")
(command "_layer" "set" "nitride" "")
(setq coupler8 nil)
(setq singlenanobeam8 nil)
(setq anglednodearray8 nil)
(setq cooledsinglenanobeam8 nil)
(setq yjunction8 nil)
; DEVICE #9
(command "_layer" "set" "window" "")
(command "_circle" "2792.915,-415" "5")
(command "_circle" "2792.915,-402.5" "5")
(command "_circle" "2792.915,-390" "5")
(command "_circle" "2792.915,-377.5" "5")
(command "_circle" "2780.415,-415" "5")
(command "_circle" "2780.415,-402.5" "5")
(command "_circle" "2780.415,-390" "5")
(command "_circle" "2780.415,-377.5" "5")
(command "_circle" "2767.915,-415" "5")
(command "_layer" "set" "nitride" "")
(setq currobj nil)
(setq currobj (ssadd))
; DRAWING COUPLER
(setq coords (list 
(list 2880.0615 -415) 
(list 2880.0615 -413) 
(list 2953.585 -413) 
(list 2953.585 -413) 
(list 2953.9677 -413.0761) 
(list 2954.2921 -413.2929) 
(list 2954.5089 -413.6173) 
(list 2954.585 -414) 
(list 2954.585 -411.8) 
(list 2954.585 -411.8) 
(list 2954.5089 -412.1827) 
(list 2954.2921 -412.5071) 
(list 2953.9677 -412.7239) 
(list 2953.585 -412.8) 
(list 2880.0615 -412.8) 
(list 2880.0615 -410.8) 
(list 2879.9385 -410.8) 
(list 2879.9385 -412.8) 
(list 2806.415 -412.8) 
(list 2806.0323 -412.7239) 
(list 2805.7079 -412.5071) 
(list 2805.4911 -412.1827) 
(list 2805.415 -411.8) 
(list 2805.415 -411.8) 
(list 2805.415 -414) 
(list 2805.4911 -413.6173) 
(list 2805.7079 -413.2929) 
(list 2806.0323 -413.0761) 
(list 2806.415 -413) 
(list 2806.415 -413) 
(list 2879.9385 -413) 
(list 2879.9385 -415)))
(apply 'command (append '("pline") coords '("c")))
(setq currobj (ssadd (entlast) currobj))
(command "._fillet" "radius" "0.3" "._fillet" "P" (entlast))
(command "_layer" "set" "holes" "")
(command "_circle" "2880,-412.9" "0.113")
(setq currobj (ssadd (entlast) currobj))
(command "_layer" "set" "nitride" "")
(command "_layer" "set" "text" "")
(command "_circle" "2879.2,-415" "0.075")
(command "_circle" "2879.2,-414.7" "0.075")
(command "_circle" "2879.2,-414.4" "0.075")
(command "_circle" "2878.9,-415" "0.075")
(command "_circle" "2878.9,-414.7" "0.075")
(command "_circle" "2878.9,-414.4" "0.075")
(command "_circle" "2878.6,-415" "0.075")
(command "_circle" "2878.6,-414.7" "0.075")
(command "_circle" "2878.6,-414.4" "0.075")
(command "_layer" "set" "nitride" "")
(command "_layer" "set" "prebias" "")
(command "_rectangle" "2805.415,-414" "2954.585,-411.8")
(setq currobj (ssadd (entlast) currobj))
(command "_rectangle" "2879.9385,-415" "2880.0615,-410.8")
(setq currobj (ssadd (entlast) currobj))
(command "_layer" "set" "nitride" "")
(setq coupler9 currobj)
(setq currobj nil)
(setq currobj (ssadd))
; DRAWING SINGLE NANOBEAM
(setq coords (list 
(list 2880.0615 -410.8) 
(list 2880.0615 -409.1417) 
(list 2880.0615 -407.4833) 
(list 2880.0615 -405.825) 
(list 2880.0615 -404.1667) 
(list 2880.0615 -402.5083) 
(list 2880.0615 -400.85) 
(list 2880.0615 -399.1917) 
(list 2880.0615 -397.5333) 
(list 2880.0616 -395.875) 
(list 2880.0616 -394.2167) 
(list 2880.0616 -392.5583) 
(list 2880.0616 -390.9) 
(list 2880.0617 -389.2417) 
(list 2880.0617 -387.5833) 
(list 2880.0617 -385.925) 
(list 2880.0618 -384.2667) 
(list 2880.0619 -382.6083) 
(list 2880.0619 -380.95) 
(list 2880.062 -379.2917) 
(list 2880.0621 -377.6333) 
(list 2880.0622 -375.975) 
(list 2880.0623 -374.3167) 
(list 2880.0624 -372.6583) 
(list 2880.0625 -371) 
(list 2880.0626 -369.3417) 
(list 2880.0628 -367.6833) 
(list 2880.0629 -366.025) 
(list 2880.0631 -364.3667) 
(list 2880.0632 -362.7083) 
(list 2880.0634 -361.05) 
(list 2880.0636 -359.3917) 
(list 2880.0638 -357.7333) 
(list 2880.0641 -356.075) 
(list 2880.0643 -354.4167) 
(list 2880.0646 -352.7583) 
(list 2880.0648 -351.1) 
(list 2880.0651 -349.4417) 
(list 2880.0654 -347.7833) 
(list 2880.0657 -346.125) 
(list 2880.0661 -344.4667) 
(list 2880.0664 -342.8083) 
(list 2880.0668 -341.15) 
(list 2880.0672 -339.4917) 
(list 2880.0676 -337.8333) 
(list 2880.068 -336.175) 
(list 2880.0685 -334.5167) 
(list 2880.0689 -332.8583) 
(list 2880.0694 -331.2) 
(list 2880.0699 -329.5417) 
(list 2880.0704 -327.8833) 
(list 2880.071 -326.225) 
(list 2880.0715 -324.5667) 
(list 2880.0721 -322.9083) 
(list 2880.0728 -321.25) 
(list 2880.0734 -319.5917) 
(list 2880.0741 -317.9333) 
(list 2880.0747 -316.275) 
(list 2880.0754 -314.6167) 
(list 2880.0762 -312.9583) 
(list 2880.0769 -311.3) 
(list 2880.0777 -309.6417) 
(list 2880.0785 -307.9833) 
(list 2880.0794 -306.325) 
(list 2880.0802 -304.6667) 
(list 2880.0811 -303.0083) 
(list 2880.082 -301.35) 
(list 2880.083 -299.6917) 
(list 2880.084 -298.0333) 
(list 2880.085 -296.375) 
(list 2880.086 -294.7167) 
(list 2880.0871 -293.0583) 
(list 2880.0882 -291.4) 
(list 2880.0893 -289.7417) 
(list 2880.0905 -288.0833) 
(list 2880.0917 -286.425) 
(list 2880.0929 -284.7667) 
(list 2880.0941 -283.1083) 
(list 2880.0954 -281.45) 
(list 2880.0967 -279.7917) 
(list 2880.0981 -278.1333) 
(list 2880.0995 -276.475) 
(list 2880.1009 -274.8167) 
(list 2880.1024 -273.1583) 
(list 2880.1039 -271.5) 
(list 2880.1054 -269.8417) 
(list 2880.107 -268.1833) 
(list 2880.1086 -266.525) 
(list 2880.1102 -264.8667) 
(list 2880.1119 -263.2083) 
(list 2880.1136 -261.55) 
(list 2880.1154 -259.8917) 
(list 2880.1172 -258.2333) 
(list 2880.119 -256.575) 
(list 2880.1209 -254.9167) 
(list 2880.1228 -253.2583) 
(list 2880.1247 -251.6) 
(list 2880.1267 -249.9417) 
(list 2880.1288 -248.2833) 
(list 2880.1308 -246.625) 
(list 2880.133 -244.9667) 
(list 2880.1351 -243.3083) 
(list 2880.1373 -241.65) 
(list 2880.1396 -239.9917) 
(list 2880.1419 -238.3333) 
(list 2880.1442 -236.675) 
(list 2880.1466 -235.0167) 
(list 2880.1491 -233.3583) 
(list 2880.1515 -231.7) 
(list 2880.1541 -230.0417) 
(list 2880.1566 -228.3833) 
(list 2880.1592 -226.725) 
(list 2880.1619 -225.0667) 
(list 2880.1646 -223.4083) 
(list 2880.1674 -221.75) 
(list 2880.1702 -220.0917) 
(list 2880.1731 -218.4333) 
(list 2880.176 -216.775) 
(list 2880.1789 -215.1167) 
(list 2880.1819 -213.4583) 
(list 2880.185 -211.8) 
(list 2879.815 -211.8) 
(list 2879.8181 -213.4583) 
(list 2879.8211 -215.1167) 
(list 2879.824 -216.775) 
(list 2879.8269 -218.4333) 
(list 2879.8298 -220.0917) 
(list 2879.8326 -221.75) 
(list 2879.8354 -223.4083) 
(list 2879.8381 -225.0667) 
(list 2879.8408 -226.725) 
(list 2879.8434 -228.3833) 
(list 2879.8459 -230.0417) 
(list 2879.8485 -231.7) 
(list 2879.8509 -233.3583) 
(list 2879.8534 -235.0167) 
(list 2879.8558 -236.675) 
(list 2879.8581 -238.3333) 
(list 2879.8604 -239.9917) 
(list 2879.8627 -241.65) 
(list 2879.8649 -243.3083) 
(list 2879.867 -244.9667) 
(list 2879.8692 -246.625) 
(list 2879.8712 -248.2833) 
(list 2879.8733 -249.9417) 
(list 2879.8753 -251.6) 
(list 2879.8772 -253.2583) 
(list 2879.8791 -254.9167) 
(list 2879.881 -256.575) 
(list 2879.8828 -258.2333) 
(list 2879.8846 -259.8917) 
(list 2879.8864 -261.55) 
(list 2879.8881 -263.2083) 
(list 2879.8898 -264.8667) 
(list 2879.8914 -266.525) 
(list 2879.893 -268.1833) 
(list 2879.8946 -269.8417) 
(list 2879.8961 -271.5) 
(list 2879.8976 -273.1583) 
(list 2879.8991 -274.8167) 
(list 2879.9005 -276.475) 
(list 2879.9019 -278.1333) 
(list 2879.9033 -279.7917) 
(list 2879.9046 -281.45) 
(list 2879.9059 -283.1083) 
(list 2879.9071 -284.7667) 
(list 2879.9083 -286.425) 
(list 2879.9095 -288.0833) 
(list 2879.9107 -289.7417) 
(list 2879.9118 -291.4) 
(list 2879.9129 -293.0583) 
(list 2879.914 -294.7167) 
(list 2879.915 -296.375) 
(list 2879.916 -298.0333) 
(list 2879.917 -299.6917) 
(list 2879.918 -301.35) 
(list 2879.9189 -303.0083) 
(list 2879.9198 -304.6667) 
(list 2879.9206 -306.325) 
(list 2879.9215 -307.9833) 
(list 2879.9223 -309.6417) 
(list 2879.9231 -311.3) 
(list 2879.9238 -312.9583) 
(list 2879.9246 -314.6167) 
(list 2879.9253 -316.275) 
(list 2879.9259 -317.9333) 
(list 2879.9266 -319.5917) 
(list 2879.9272 -321.25) 
(list 2879.9279 -322.9083) 
(list 2879.9285 -324.5667) 
(list 2879.929 -326.225) 
(list 2879.9296 -327.8833) 
(list 2879.9301 -329.5417) 
(list 2879.9306 -331.2) 
(list 2879.9311 -332.8583) 
(list 2879.9315 -334.5167) 
(list 2879.932 -336.175) 
(list 2879.9324 -337.8333) 
(list 2879.9328 -339.4917) 
(list 2879.9332 -341.15) 
(list 2879.9336 -342.8083) 
(list 2879.9339 -344.4667) 
(list 2879.9343 -346.125) 
(list 2879.9346 -347.7833) 
(list 2879.9349 -349.4417) 
(list 2879.9352 -351.1) 
(list 2879.9354 -352.7583) 
(list 2879.9357 -354.4167) 
(list 2879.9359 -356.075) 
(list 2879.9362 -357.7333) 
(list 2879.9364 -359.3917) 
(list 2879.9366 -361.05) 
(list 2879.9368 -362.7083) 
(list 2879.9369 -364.3667) 
(list 2879.9371 -366.025) 
(list 2879.9372 -367.6833) 
(list 2879.9374 -369.3417) 
(list 2879.9375 -371) 
(list 2879.9376 -372.6583) 
(list 2879.9377 -374.3167) 
(list 2879.9378 -375.975) 
(list 2879.9379 -377.6333) 
(list 2879.938 -379.2917) 
(list 2879.9381 -380.95) 
(list 2879.9381 -382.6083) 
(list 2879.9382 -384.2667) 
(list 2879.9383 -385.925) 
(list 2879.9383 -387.5833) 
(list 2879.9383 -389.2417) 
(list 2879.9384 -390.9) 
(list 2879.9384 -392.5583) 
(list 2879.9384 -394.2167) 
(list 2879.9384 -395.875) 
(list 2879.9385 -397.5333) 
(list 2879.9385 -399.1917) 
(list 2879.9385 -400.85) 
(list 2879.9385 -402.5083) 
(list 2879.9385 -404.1667) 
(list 2879.9385 -405.825) 
(list 2879.9385 -407.4833) 
(list 2879.9385 -409.1417) 
(list 2879.9385 -410.8)))
(apply 'command (append '("pline") coords '("c")))
(setq currobj (ssadd (entlast) currobj))
(command "_layer" "set" "prebias" "")
(command "_rectangle" "2879.815,-410.8" "2880.185,-211.8")
(setq currobj (ssadd (entlast) currobj))
(command "_layer" "set" "nitride" "")
(setq singlenanobeam9 currobj)
(setq currobj nil)
(setq currobj (ssadd))
; DRAWING NODE ARRAY
(setq coords (list 
(list 2880.185 -211.8) 
(list 2880.5625 -201.8) 
(list 2880.5625 -201.8) 
(list 2880.5625 -200.8) 
(list 2954.585 -212.6864) 
(list 2954.585 -207.7434) 
(list 2880.5625 -197.357) 
(list 2880.5625 -196.357) 
(list 2880.5625 -196.357) 
(list 2880.2625 -186.357) 
(list 2879.7375 -186.357) 
(list 2879.4375 -196.357) 
(list 2879.4375 -196.357) 
(list 2879.4375 -197.357) 
(list 2805.415 -207.7434) 
(list 2805.415 -212.6864) 
(list 2879.4375 -200.8) 
(list 2879.4375 -201.8) 
(list 2879.4375 -201.8) 
(list 2879.815 -211.8)))
(apply 'command (append '("pline") coords '("c")))
(setq currobj (ssadd (entlast) currobj))
(command "_layer" "set" "prebias" "")
(setq coords (list 
(list 2879.4375 -212.6864) 
(list 2879.4375 -200.8) 
(list 2805.415 -212.6864) 
(list 2805.415 -207.7434) 
(list 2879.4375 -197.357) 
(list 2879.4375 -186.357) 
(list 2880.5625 -186.357) 
(list 2880.5625 -197.357) 
(list 2954.585 -207.7434) 
(list 2954.585 -212.6864) 
(list 2880.5625 -200.8) 
(list 2880.5625 -212.6864)))
(apply 'command (append '("pline") coords '("c")))
(setq currobj (ssadd (entlast) currobj))
(command "_layer" "set" "nitride" "")
(command "_layer" "set" "fda1" "")
(setq coords (list 
(list 2880.5625 -200.657) 
(list 2954.585 -212.5434) 
(list 2954.585 -212.3664) 
(list 2880.5625 -200.58)))
(apply 'command (append '("pline") coords '("c")))
(setq currobj (ssadd (entlast) currobj))
(setq coords (list 
(list 2880.5625 -200.437) 
(list 2954.585 -212.2234) 
(list 2954.585 -212.0464) 
(list 2880.5625 -200.36)))
(apply 'command (append '("pline") coords '("c")))
(setq currobj (ssadd (entlast) currobj))
(setq coords (list 
(list 2880.5625 -200.217) 
(list 2954.585 -211.9034) 
(list 2954.585 -211.7264) 
(list 2880.5625 -200.14)))
(apply 'command (append '("pline") coords '("c")))
(setq currobj (ssadd (entlast) currobj))
(setq coords (list 
(list 2880.5625 -199.997) 
(list 2954.585 -211.5834) 
(list 2954.585 -211.4064) 
(list 2880.5625 -199.92)))
(apply 'command (append '("pline") coords '("c")))
(setq currobj (ssadd (entlast) currobj))
(setq coords (list 
(list 2880.5625 -199.777) 
(list 2954.585 -211.2634) 
(list 2954.585 -211.0864) 
(list 2880.5625 -199.7)))
(apply 'command (append '("pline") coords '("c")))
(setq currobj (ssadd (entlast) currobj))
(setq coords (list 
(list 2880.5625 -199.557) 
(list 2954.585 -210.9434) 
(list 2954.585 -210.7664) 
(list 2880.5625 -199.48)))
(apply 'command (append '("pline") coords '("c")))
(setq currobj (ssadd (entlast) currobj))
(setq coords (list 
(list 2880.5625 -199.337) 
(list 2954.585 -210.6234) 
(list 2954.585 -210.4464) 
(list 2880.5625 -199.26)))
(apply 'command (append '("pline") coords '("c")))
(setq currobj (ssadd (entlast) currobj))
(setq coords (list 
(list 2880.5625 -199.117) 
(list 2954.585 -210.3034) 
(list 2954.585 -210.1264) 
(list 2880.5625 -199.04)))
(apply 'command (append '("pline") coords '("c")))
(setq currobj (ssadd (entlast) currobj))
(setq coords (list 
(list 2880.5625 -198.897) 
(list 2954.585 -209.9834) 
(list 2954.585 -209.8064) 
(list 2880.5625 -198.82)))
(apply 'command (append '("pline") coords '("c")))
(setq currobj (ssadd (entlast) currobj))
(setq coords (list 
(list 2880.5625 -198.677) 
(list 2954.585 -209.6634) 
(list 2954.585 -209.4864) 
(list 2880.5625 -198.6)))
(apply 'command (append '("pline") coords '("c")))
(setq currobj (ssadd (entlast) currobj))
(setq coords (list 
(list 2880.5625 -198.457) 
(list 2954.585 -209.3434) 
(list 2954.585 -209.1664) 
(list 2880.5625 -198.38)))
(apply 'command (append '("pline") coords '("c")))
(setq currobj (ssadd (entlast) currobj))
(setq coords (list 
(list 2880.5625 -198.237) 
(list 2954.585 -209.0234) 
(list 2954.585 -208.8464) 
(list 2880.5625 -198.16)))
(apply 'command (append '("pline") coords '("c")))
(setq currobj (ssadd (entlast) currobj))
(setq coords (list 
(list 2880.5625 -198.017) 
(list 2954.585 -208.7034) 
(list 2954.585 -208.5264) 
(list 2880.5625 -197.94)))
(apply 'command (append '("pline") coords '("c")))
(setq currobj (ssadd (entlast) currobj))
(setq coords (list 
(list 2880.5625 -197.797) 
(list 2954.585 -208.3834) 
(list 2954.585 -208.2064) 
(list 2880.5625 -197.72)))
(apply 'command (append '("pline") coords '("c")))
(setq currobj (ssadd (entlast) currobj))
(setq coords (list 
(list 2880.5625 -197.577) 
(list 2954.585 -208.0634) 
(list 2954.585 -207.8864) 
(list 2880.5625 -197.5)))
(apply 'command (append '("pline") coords '("c")))
(setq currobj (ssadd (entlast) currobj))
(setq coords (list 
(list 2879.4375 -197.5) 
(list 2805.415 -207.8864) 
(list 2805.415 -208.0634) 
(list 2879.4375 -197.577)))
(apply 'command (append '("pline") coords '("c")))
(setq currobj (ssadd (entlast) currobj))
(setq coords (list 
(list 2879.4375 -197.72) 
(list 2805.415 -208.2064) 
(list 2805.415 -208.3834) 
(list 2879.4375 -197.797)))
(apply 'command (append '("pline") coords '("c")))
(setq currobj (ssadd (entlast) currobj))
(setq coords (list 
(list 2879.4375 -197.94) 
(list 2805.415 -208.5264) 
(list 2805.415 -208.7034) 
(list 2879.4375 -198.017)))
(apply 'command (append '("pline") coords '("c")))
(setq currobj (ssadd (entlast) currobj))
(setq coords (list 
(list 2879.4375 -198.16) 
(list 2805.415 -208.8464) 
(list 2805.415 -209.0234) 
(list 2879.4375 -198.237)))
(apply 'command (append '("pline") coords '("c")))
(setq currobj (ssadd (entlast) currobj))
(setq coords (list 
(list 2879.4375 -198.38) 
(list 2805.415 -209.1664) 
(list 2805.415 -209.3434) 
(list 2879.4375 -198.457)))
(apply 'command (append '("pline") coords '("c")))
(setq currobj (ssadd (entlast) currobj))
(setq coords (list 
(list 2879.4375 -198.6) 
(list 2805.415 -209.4864) 
(list 2805.415 -209.6634) 
(list 2879.4375 -198.677)))
(apply 'command (append '("pline") coords '("c")))
(setq currobj (ssadd (entlast) currobj))
(setq coords (list 
(list 2879.4375 -198.82) 
(list 2805.415 -209.8064) 
(list 2805.415 -209.9834) 
(list 2879.4375 -198.897)))
(apply 'command (append '("pline") coords '("c")))
(setq currobj (ssadd (entlast) currobj))
(setq coords (list 
(list 2879.4375 -199.04) 
(list 2805.415 -210.1264) 
(list 2805.415 -210.3034) 
(list 2879.4375 -199.117)))
(apply 'command (append '("pline") coords '("c")))
(setq currobj (ssadd (entlast) currobj))
(setq coords (list 
(list 2879.4375 -199.26) 
(list 2805.415 -210.4464) 
(list 2805.415 -210.6234) 
(list 2879.4375 -199.337)))
(apply 'command (append '("pline") coords '("c")))
(setq currobj (ssadd (entlast) currobj))
(setq coords (list 
(list 2879.4375 -199.48) 
(list 2805.415 -210.7664) 
(list 2805.415 -210.9434) 
(list 2879.4375 -199.557)))
(apply 'command (append '("pline") coords '("c")))
(setq currobj (ssadd (entlast) currobj))
(setq coords (list 
(list 2879.4375 -199.7) 
(list 2805.415 -211.0864) 
(list 2805.415 -211.2634) 
(list 2879.4375 -199.777)))
(apply 'command (append '("pline") coords '("c")))
(setq currobj (ssadd (entlast) currobj))
(setq coords (list 
(list 2879.4375 -199.92) 
(list 2805.415 -211.4064) 
(list 2805.415 -211.5834) 
(list 2879.4375 -199.997)))
(apply 'command (append '("pline") coords '("c")))
(setq currobj (ssadd (entlast) currobj))
(setq coords (list 
(list 2879.4375 -200.14) 
(list 2805.415 -211.7264) 
(list 2805.415 -211.9034) 
(list 2879.4375 -200.217)))
(apply 'command (append '("pline") coords '("c")))
(setq currobj (ssadd (entlast) currobj))
(setq coords (list 
(list 2879.4375 -200.36) 
(list 2805.415 -212.0464) 
(list 2805.415 -212.2234) 
(list 2879.4375 -200.437)))
(apply 'command (append '("pline") coords '("c")))
(setq currobj (ssadd (entlast) currobj))
(setq coords (list 
(list 2879.4375 -200.58) 
(list 2805.415 -212.3664) 
(list 2805.415 -212.5434) 
(list 2879.4375 -200.657)))
(apply 'command (append '("pline") coords '("c")))
(setq currobj (ssadd (entlast) currobj))
(command "_layer" "set" "nitride" "")
(command "_layer" "set" "text" "")
(command "_circle" "2878.985,-211.8" "0.075")
(command "_circle" "2878.985,-211.5" "0.075")
(command "_circle" "2878.985,-211.2" "0.075")
(command "_circle" "2878.985,-210.9" "0.075")
(command "_circle" "2878.985,-210.6" "0.075")
(command "_circle" "2878.685,-211.8" "0.075")
(command "_circle" "2878.685,-211.5" "0.075")
(command "_circle" "2878.685,-211.2" "0.075")
(command "_circle" "2878.685,-210.9" "0.075")
(command "_circle" "2878.685,-210.6" "0.075")
(command "_circle" "2878.385,-211.8" "0.075")
(command "_circle" "2878.385,-211.5" "0.075")
(command "_circle" "2878.385,-211.2" "0.075")
(command "_circle" "2878.385,-210.9" "0.075")
(command "_circle" "2878.385,-210.6" "0.075")
(command "_circle" "2878.085,-211.8" "0.075")
(command "_circle" "2878.085,-211.5" "0.075")
(command "_circle" "2878.085,-211.2" "0.075")
(command "_circle" "2878.085,-210.9" "0.075")
(command "_circle" "2878.085,-210.6" "0.075")
(command "_circle" "2877.785,-211.8" "0.075")
(command "_circle" "2877.785,-211.5" "0.075")
(command "_circle" "2877.785,-211.2" "0.075")
(command "_circle" "2877.785,-210.9" "0.075")
(command "_circle" "2877.785,-210.6" "0.075")
(command "_layer" "set" "nitride" "")
(setq anglednodearray9 currobj)
(setq currobj nil)
(setq currobj (ssadd))
; DRAWING COOLED SINGLE NANOBEAM
(setq coords (list 
(list 2880.2625 -186.357) 
(list 2880.2625 -181.357) 
(list 2879.7375 -181.357) 
(list 2879.7375 -186.357)))
(apply 'command (append '("pline") coords '("c")))
(setq currobj (ssadd (entlast) currobj))
(command "_layer" "set" "prebias" "")
(command "_rectangle" "2879.7375,-186.357" "2880.2625,-181.357")
(setq currobj (ssadd (entlast) currobj))
(command "_layer" "set" "nitride" "")
(setq coords (list 
(list 2880.2625 -181.357) 
(list 2880.5625 -171.357) 
(list 2880.5625 -171.357) 
(list 2880.5625 -170.357) 
(list 2954.585 -171.107) 
(list 2954.585 -166.164) 
(list 2880.5625 -166.914) 
(list 2880.5625 -165.914) 
(list 2880.5625 -165.914) 
(list 2880.2625 -155.914) 
(list 2879.7375 -155.914) 
(list 2879.4375 -165.914) 
(list 2879.4375 -165.914) 
(list 2879.4375 -166.914) 
(list 2805.415 -166.164) 
(list 2805.415 -171.107) 
(list 2879.4375 -170.357) 
(list 2879.4375 -171.357) 
(list 2879.4375 -171.357) 
(list 2879.7375 -181.357)))
(apply 'command (append '("pline") coords '("c")))
(setq currobj (ssadd (entlast) currobj))
(command "_layer" "set" "prebias" "")
(setq coords (list 
(list 2879.4375 -181.357) 
(list 2879.4375 -170.357) 
(list 2805.415 -171.107) 
(list 2805.415 -166.164) 
(list 2879.4375 -166.914) 
(list 2879.4375 -155.914) 
(list 2880.5625 -155.914) 
(list 2880.5625 -166.914) 
(list 2954.585 -166.164) 
(list 2954.585 -171.107) 
(list 2880.5625 -170.357) 
(list 2880.5625 -181.357)))
(apply 'command (append '("pline") coords '("c")))
(setq currobj (ssadd (entlast) currobj))
(command "_layer" "set" "nitride" "")
(command "_layer" "set" "fda1" "")
(setq coords (list 
(list 2880.5625 -170.214) 
(list 2954.585 -170.964) 
(list 2954.585 -170.787) 
(list 2880.5625 -170.137)))
(apply 'command (append '("pline") coords '("c")))
(setq currobj (ssadd (entlast) currobj))
(setq coords (list 
(list 2880.5625 -169.994) 
(list 2954.585 -170.644) 
(list 2954.585 -170.467) 
(list 2880.5625 -169.917)))
(apply 'command (append '("pline") coords '("c")))
(setq currobj (ssadd (entlast) currobj))
(setq coords (list 
(list 2880.5625 -169.774) 
(list 2954.585 -170.324) 
(list 2954.585 -170.147) 
(list 2880.5625 -169.697)))
(apply 'command (append '("pline") coords '("c")))
(setq currobj (ssadd (entlast) currobj))
(setq coords (list 
(list 2880.5625 -169.554) 
(list 2954.585 -170.004) 
(list 2954.585 -169.827) 
(list 2880.5625 -169.477)))
(apply 'command (append '("pline") coords '("c")))
(setq currobj (ssadd (entlast) currobj))
(setq coords (list 
(list 2880.5625 -169.334) 
(list 2954.585 -169.684) 
(list 2954.585 -169.507) 
(list 2880.5625 -169.257)))
(apply 'command (append '("pline") coords '("c")))
(setq currobj (ssadd (entlast) currobj))
(setq coords (list 
(list 2880.5625 -169.114) 
(list 2954.585 -169.364) 
(list 2954.585 -169.187) 
(list 2880.5625 -169.037)))
(apply 'command (append '("pline") coords '("c")))
(setq currobj (ssadd (entlast) currobj))
(setq coords (list 
(list 2880.5625 -168.894) 
(list 2954.585 -169.044) 
(list 2954.585 -168.867) 
(list 2880.5625 -168.817)))
(apply 'command (append '("pline") coords '("c")))
(setq currobj (ssadd (entlast) currobj))
(setq coords (list 
(list 2880.5625 -168.674) 
(list 2954.585 -168.724) 
(list 2954.585 -168.547) 
(list 2880.5625 -168.597)))
(apply 'command (append '("pline") coords '("c")))
(setq currobj (ssadd (entlast) currobj))
(setq coords (list 
(list 2880.5625 -168.454) 
(list 2954.585 -168.404) 
(list 2954.585 -168.227) 
(list 2880.5625 -168.377)))
(apply 'command (append '("pline") coords '("c")))
(setq currobj (ssadd (entlast) currobj))
(setq coords (list 
(list 2880.5625 -168.234) 
(list 2954.585 -168.084) 
(list 2954.585 -167.907) 
(list 2880.5625 -168.157)))
(apply 'command (append '("pline") coords '("c")))
(setq currobj (ssadd (entlast) currobj))
(setq coords (list 
(list 2880.5625 -168.014) 
(list 2954.585 -167.764) 
(list 2954.585 -167.587) 
(list 2880.5625 -167.937)))
(apply 'command (append '("pline") coords '("c")))
(setq currobj (ssadd (entlast) currobj))
(setq coords (list 
(list 2880.5625 -167.794) 
(list 2954.585 -167.444) 
(list 2954.585 -167.267) 
(list 2880.5625 -167.717)))
(apply 'command (append '("pline") coords '("c")))
(setq currobj (ssadd (entlast) currobj))
(setq coords (list 
(list 2880.5625 -167.574) 
(list 2954.585 -167.124) 
(list 2954.585 -166.947) 
(list 2880.5625 -167.497)))
(apply 'command (append '("pline") coords '("c")))
(setq currobj (ssadd (entlast) currobj))
(setq coords (list 
(list 2880.5625 -167.354) 
(list 2954.585 -166.804) 
(list 2954.585 -166.627) 
(list 2880.5625 -167.277)))
(apply 'command (append '("pline") coords '("c")))
(setq currobj (ssadd (entlast) currobj))
(setq coords (list 
(list 2880.5625 -167.134) 
(list 2954.585 -166.484) 
(list 2954.585 -166.307) 
(list 2880.5625 -167.057)))
(apply 'command (append '("pline") coords '("c")))
(setq currobj (ssadd (entlast) currobj))
(setq coords (list 
(list 2879.4375 -167.057) 
(list 2805.415 -166.307) 
(list 2805.415 -166.484) 
(list 2879.4375 -167.134)))
(apply 'command (append '("pline") coords '("c")))
(setq currobj (ssadd (entlast) currobj))
(setq coords (list 
(list 2879.4375 -167.277) 
(list 2805.415 -166.627) 
(list 2805.415 -166.804) 
(list 2879.4375 -167.354)))
(apply 'command (append '("pline") coords '("c")))
(setq currobj (ssadd (entlast) currobj))
(setq coords (list 
(list 2879.4375 -167.497) 
(list 2805.415 -166.947) 
(list 2805.415 -167.124) 
(list 2879.4375 -167.574)))
(apply 'command (append '("pline") coords '("c")))
(setq currobj (ssadd (entlast) currobj))
(setq coords (list 
(list 2879.4375 -167.717) 
(list 2805.415 -167.267) 
(list 2805.415 -167.444) 
(list 2879.4375 -167.794)))
(apply 'command (append '("pline") coords '("c")))
(setq currobj (ssadd (entlast) currobj))
(setq coords (list 
(list 2879.4375 -167.937) 
(list 2805.415 -167.587) 
(list 2805.415 -167.764) 
(list 2879.4375 -168.014)))
(apply 'command (append '("pline") coords '("c")))
(setq currobj (ssadd (entlast) currobj))
(setq coords (list 
(list 2879.4375 -168.157) 
(list 2805.415 -167.907) 
(list 2805.415 -168.084) 
(list 2879.4375 -168.234)))
(apply 'command (append '("pline") coords '("c")))
(setq currobj (ssadd (entlast) currobj))
(setq coords (list 
(list 2879.4375 -168.377) 
(list 2805.415 -168.227) 
(list 2805.415 -168.404) 
(list 2879.4375 -168.454)))
(apply 'command (append '("pline") coords '("c")))
(setq currobj (ssadd (entlast) currobj))
(setq coords (list 
(list 2879.4375 -168.597) 
(list 2805.415 -168.547) 
(list 2805.415 -168.724) 
(list 2879.4375 -168.674)))
(apply 'command (append '("pline") coords '("c")))
(setq currobj (ssadd (entlast) currobj))
(setq coords (list 
(list 2879.4375 -168.817) 
(list 2805.415 -168.867) 
(list 2805.415 -169.044) 
(list 2879.4375 -168.894)))
(apply 'command (append '("pline") coords '("c")))
(setq currobj (ssadd (entlast) currobj))
(setq coords (list 
(list 2879.4375 -169.037) 
(list 2805.415 -169.187) 
(list 2805.415 -169.364) 
(list 2879.4375 -169.114)))
(apply 'command (append '("pline") coords '("c")))
(setq currobj (ssadd (entlast) currobj))
(setq coords (list 
(list 2879.4375 -169.257) 
(list 2805.415 -169.507) 
(list 2805.415 -169.684) 
(list 2879.4375 -169.334)))
(apply 'command (append '("pline") coords '("c")))
(setq currobj (ssadd (entlast) currobj))
(setq coords (list 
(list 2879.4375 -169.477) 
(list 2805.415 -169.827) 
(list 2805.415 -170.004) 
(list 2879.4375 -169.554)))
(apply 'command (append '("pline") coords '("c")))
(setq currobj (ssadd (entlast) currobj))
(setq coords (list 
(list 2879.4375 -169.697) 
(list 2805.415 -170.147) 
(list 2805.415 -170.324) 
(list 2879.4375 -169.774)))
(apply 'command (append '("pline") coords '("c")))
(setq currobj (ssadd (entlast) currobj))
(setq coords (list 
(list 2879.4375 -169.917) 
(list 2805.415 -170.467) 
(list 2805.415 -170.644) 
(list 2879.4375 -169.994)))
(apply 'command (append '("pline") coords '("c")))
(setq currobj (ssadd (entlast) currobj))
(setq coords (list 
(list 2879.4375 -170.137) 
(list 2805.415 -170.787) 
(list 2805.415 -170.964) 
(list 2879.4375 -170.214)))
(apply 'command (append '("pline") coords '("c")))
(setq currobj (ssadd (entlast) currobj))
(command "_layer" "set" "nitride" "")
(command "_layer" "set" "text" "")
(command "_circle" "2879.0625,-181.357" "0.075")
(command "_circle" "2879.0625,-181.057" "0.075")
(command "_circle" "2879.0625,-180.757" "0.075")
(command "_circle" "2879.0625,-180.457" "0.075")
(command "_circle" "2879.0625,-180.157" "0.075")
(command "_circle" "2878.7625,-181.357" "0.075")
(command "_circle" "2878.7625,-181.057" "0.075")
(command "_circle" "2878.7625,-180.757" "0.075")
(command "_circle" "2878.7625,-180.457" "0.075")
(command "_circle" "2878.7625,-180.157" "0.075")
(command "_circle" "2878.4625,-181.357" "0.075")
(command "_circle" "2878.4625,-181.057" "0.075")
(command "_circle" "2878.4625,-180.757" "0.075")
(command "_circle" "2878.4625,-180.457" "0.075")
(command "_circle" "2878.4625,-180.157" "0.075")
(command "_circle" "2878.1625,-181.357" "0.075")
(command "_circle" "2878.1625,-181.057" "0.075")
(command "_circle" "2878.1625,-180.757" "0.075")
(command "_circle" "2878.1625,-180.457" "0.075")
(command "_circle" "2878.1625,-180.157" "0.075")
(command "_circle" "2877.8625,-181.357" "0.075")
(command "_circle" "2877.8625,-181.057" "0.075")
(command "_circle" "2877.8625,-180.757" "0.075")
(command "_circle" "2877.8625,-180.457" "0.075")
(command "_circle" "2877.8625,-180.157" "0.075")
(command "_layer" "set" "nitride" "")
(setq coords (list 
(list 2880.2625 -155.914) 
(list 2880.2625 -40.2693) 
(list 2879.7375 -40.2693) 
(list 2879.7375 -155.914)))
(apply 'command (append '("pline") coords '("c")))
(setq currobj (ssadd (entlast) currobj))
(command "_layer" "set" "prebias" "")
(command "_rectangle" "2879.7375,-155.914" "2880.2625,-40.2693")
(setq currobj (ssadd (entlast) currobj))
(command "_layer" "set" "nitride" "")
(setq coords (list 
(list 2880.2625 -40.2693) 
(list 2880.5625 -30.2693) 
(list 2880.5625 -30.2693) 
(list 2880.5625 -29.2693) 
(list 2954.585 -30.0193) 
(list 2954.585 -25.0763) 
(list 2880.5625 -25.8263) 
(list 2880.5625 -24.8263) 
(list 2880.5625 -24.8263) 
(list 2880.2625 -14.8263) 
(list 2879.7375 -14.8263) 
(list 2879.4375 -24.8263) 
(list 2879.4375 -24.8263) 
(list 2879.4375 -25.8263) 
(list 2805.415 -25.0763) 
(list 2805.415 -30.0193) 
(list 2879.4375 -29.2693) 
(list 2879.4375 -30.2693) 
(list 2879.4375 -30.2693) 
(list 2879.7375 -40.2693)))
(apply 'command (append '("pline") coords '("c")))
(setq currobj (ssadd (entlast) currobj))
(command "_layer" "set" "prebias" "")
(setq coords (list 
(list 2879.4375 -40.2693) 
(list 2879.4375 -29.2693) 
(list 2805.415 -30.0193) 
(list 2805.415 -25.0763) 
(list 2879.4375 -25.8263) 
(list 2879.4375 -14.8263) 
(list 2880.5625 -14.8263) 
(list 2880.5625 -25.8263) 
(list 2954.585 -25.0763) 
(list 2954.585 -30.0193) 
(list 2880.5625 -29.2693) 
(list 2880.5625 -40.2693)))
(apply 'command (append '("pline") coords '("c")))
(setq currobj (ssadd (entlast) currobj))
(command "_layer" "set" "nitride" "")
(command "_layer" "set" "fda1" "")
(setq coords (list 
(list 2880.5625 -29.1263) 
(list 2954.585 -29.8763) 
(list 2954.585 -29.6993) 
(list 2880.5625 -29.0493)))
(apply 'command (append '("pline") coords '("c")))
(setq currobj (ssadd (entlast) currobj))
(setq coords (list 
(list 2880.5625 -28.9063) 
(list 2954.585 -29.5563) 
(list 2954.585 -29.3793) 
(list 2880.5625 -28.8293)))
(apply 'command (append '("pline") coords '("c")))
(setq currobj (ssadd (entlast) currobj))
(setq coords (list 
(list 2880.5625 -28.6863) 
(list 2954.585 -29.2363) 
(list 2954.585 -29.0593) 
(list 2880.5625 -28.6093)))
(apply 'command (append '("pline") coords '("c")))
(setq currobj (ssadd (entlast) currobj))
(setq coords (list 
(list 2880.5625 -28.4663) 
(list 2954.585 -28.9163) 
(list 2954.585 -28.7393) 
(list 2880.5625 -28.3893)))
(apply 'command (append '("pline") coords '("c")))
(setq currobj (ssadd (entlast) currobj))
(setq coords (list 
(list 2880.5625 -28.2463) 
(list 2954.585 -28.5963) 
(list 2954.585 -28.4193) 
(list 2880.5625 -28.1693)))
(apply 'command (append '("pline") coords '("c")))
(setq currobj (ssadd (entlast) currobj))
(setq coords (list 
(list 2880.5625 -28.0263) 
(list 2954.585 -28.2763) 
(list 2954.585 -28.0993) 
(list 2880.5625 -27.9493)))
(apply 'command (append '("pline") coords '("c")))
(setq currobj (ssadd (entlast) currobj))
(setq coords (list 
(list 2880.5625 -27.8063) 
(list 2954.585 -27.9563) 
(list 2954.585 -27.7793) 
(list 2880.5625 -27.7293)))
(apply 'command (append '("pline") coords '("c")))
(setq currobj (ssadd (entlast) currobj))
(setq coords (list 
(list 2880.5625 -27.5863) 
(list 2954.585 -27.6363) 
(list 2954.585 -27.4593) 
(list 2880.5625 -27.5093)))
(apply 'command (append '("pline") coords '("c")))
(setq currobj (ssadd (entlast) currobj))
(setq coords (list 
(list 2880.5625 -27.3663) 
(list 2954.585 -27.3163) 
(list 2954.585 -27.1393) 
(list 2880.5625 -27.2893)))
(apply 'command (append '("pline") coords '("c")))
(setq currobj (ssadd (entlast) currobj))
(setq coords (list 
(list 2880.5625 -27.1463) 
(list 2954.585 -26.9963) 
(list 2954.585 -26.8193) 
(list 2880.5625 -27.0693)))
(apply 'command (append '("pline") coords '("c")))
(setq currobj (ssadd (entlast) currobj))
(setq coords (list 
(list 2880.5625 -26.9263) 
(list 2954.585 -26.6763) 
(list 2954.585 -26.4993) 
(list 2880.5625 -26.8493)))
(apply 'command (append '("pline") coords '("c")))
(setq currobj (ssadd (entlast) currobj))
(setq coords (list 
(list 2880.5625 -26.7063) 
(list 2954.585 -26.3563) 
(list 2954.585 -26.1793) 
(list 2880.5625 -26.6293)))
(apply 'command (append '("pline") coords '("c")))
(setq currobj (ssadd (entlast) currobj))
(setq coords (list 
(list 2880.5625 -26.4863) 
(list 2954.585 -26.0363) 
(list 2954.585 -25.8593) 
(list 2880.5625 -26.4093)))
(apply 'command (append '("pline") coords '("c")))
(setq currobj (ssadd (entlast) currobj))
(setq coords (list 
(list 2880.5625 -26.2663) 
(list 2954.585 -25.7163) 
(list 2954.585 -25.5393) 
(list 2880.5625 -26.1893)))
(apply 'command (append '("pline") coords '("c")))
(setq currobj (ssadd (entlast) currobj))
(setq coords (list 
(list 2880.5625 -26.0463) 
(list 2954.585 -25.3963) 
(list 2954.585 -25.2193) 
(list 2880.5625 -25.9693)))
(apply 'command (append '("pline") coords '("c")))
(setq currobj (ssadd (entlast) currobj))
(setq coords (list 
(list 2879.4375 -25.9693) 
(list 2805.415 -25.2193) 
(list 2805.415 -25.3963) 
(list 2879.4375 -26.0463)))
(apply 'command (append '("pline") coords '("c")))
(setq currobj (ssadd (entlast) currobj))
(setq coords (list 
(list 2879.4375 -26.1893) 
(list 2805.415 -25.5393) 
(list 2805.415 -25.7163) 
(list 2879.4375 -26.2663)))
(apply 'command (append '("pline") coords '("c")))
(setq currobj (ssadd (entlast) currobj))
(setq coords (list 
(list 2879.4375 -26.4093) 
(list 2805.415 -25.8593) 
(list 2805.415 -26.0363) 
(list 2879.4375 -26.4863)))
(apply 'command (append '("pline") coords '("c")))
(setq currobj (ssadd (entlast) currobj))
(setq coords (list 
(list 2879.4375 -26.6293) 
(list 2805.415 -26.1793) 
(list 2805.415 -26.3563) 
(list 2879.4375 -26.7063)))
(apply 'command (append '("pline") coords '("c")))
(setq currobj (ssadd (entlast) currobj))
(setq coords (list 
(list 2879.4375 -26.8493) 
(list 2805.415 -26.4993) 
(list 2805.415 -26.6763) 
(list 2879.4375 -26.9263)))
(apply 'command (append '("pline") coords '("c")))
(setq currobj (ssadd (entlast) currobj))
(setq coords (list 
(list 2879.4375 -27.0693) 
(list 2805.415 -26.8193) 
(list 2805.415 -26.9963) 
(list 2879.4375 -27.1463)))
(apply 'command (append '("pline") coords '("c")))
(setq currobj (ssadd (entlast) currobj))
(setq coords (list 
(list 2879.4375 -27.2893) 
(list 2805.415 -27.1393) 
(list 2805.415 -27.3163) 
(list 2879.4375 -27.3663)))
(apply 'command (append '("pline") coords '("c")))
(setq currobj (ssadd (entlast) currobj))
(setq coords (list 
(list 2879.4375 -27.5093) 
(list 2805.415 -27.4593) 
(list 2805.415 -27.6363) 
(list 2879.4375 -27.5863)))
(apply 'command (append '("pline") coords '("c")))
(setq currobj (ssadd (entlast) currobj))
(setq coords (list 
(list 2879.4375 -27.7293) 
(list 2805.415 -27.7793) 
(list 2805.415 -27.9563) 
(list 2879.4375 -27.8063)))
(apply 'command (append '("pline") coords '("c")))
(setq currobj (ssadd (entlast) currobj))
(setq coords (list 
(list 2879.4375 -27.9493) 
(list 2805.415 -28.0993) 
(list 2805.415 -28.2763) 
(list 2879.4375 -28.0263)))
(apply 'command (append '("pline") coords '("c")))
(setq currobj (ssadd (entlast) currobj))
(setq coords (list 
(list 2879.4375 -28.1693) 
(list 2805.415 -28.4193) 
(list 2805.415 -28.5963) 
(list 2879.4375 -28.2463)))
(apply 'command (append '("pline") coords '("c")))
(setq currobj (ssadd (entlast) currobj))
(setq coords (list 
(list 2879.4375 -28.3893) 
(list 2805.415 -28.7393) 
(list 2805.415 -28.9163) 
(list 2879.4375 -28.4663)))
(apply 'command (append '("pline") coords '("c")))
(setq currobj (ssadd (entlast) currobj))
(setq coords (list 
(list 2879.4375 -28.6093) 
(list 2805.415 -29.0593) 
(list 2805.415 -29.2363) 
(list 2879.4375 -28.6863)))
(apply 'command (append '("pline") coords '("c")))
(setq currobj (ssadd (entlast) currobj))
(setq coords (list 
(list 2879.4375 -28.8293) 
(list 2805.415 -29.3793) 
(list 2805.415 -29.5563) 
(list 2879.4375 -28.9063)))
(apply 'command (append '("pline") coords '("c")))
(setq currobj (ssadd (entlast) currobj))
(setq coords (list 
(list 2879.4375 -29.0493) 
(list 2805.415 -29.6993) 
(list 2805.415 -29.8763) 
(list 2879.4375 -29.1263)))
(apply 'command (append '("pline") coords '("c")))
(setq currobj (ssadd (entlast) currobj))
(command "_layer" "set" "nitride" "")
(command "_layer" "set" "text" "")
(command "_circle" "2879.0625,-40.2693" "0.075")
(command "_circle" "2879.0625,-39.9693" "0.075")
(command "_circle" "2879.0625,-39.6693" "0.075")
(command "_circle" "2879.0625,-39.3693" "0.075")
(command "_circle" "2879.0625,-39.0693" "0.075")
(command "_circle" "2878.7625,-40.2693" "0.075")
(command "_circle" "2878.7625,-39.9693" "0.075")
(command "_circle" "2878.7625,-39.6693" "0.075")
(command "_circle" "2878.7625,-39.3693" "0.075")
(command "_circle" "2878.7625,-39.0693" "0.075")
(command "_circle" "2878.4625,-40.2693" "0.075")
(command "_circle" "2878.4625,-39.9693" "0.075")
(command "_circle" "2878.4625,-39.6693" "0.075")
(command "_circle" "2878.4625,-39.3693" "0.075")
(command "_circle" "2878.4625,-39.0693" "0.075")
(command "_circle" "2878.1625,-40.2693" "0.075")
(command "_circle" "2878.1625,-39.9693" "0.075")
(command "_circle" "2878.1625,-39.6693" "0.075")
(command "_circle" "2878.1625,-39.3693" "0.075")
(command "_circle" "2878.1625,-39.0693" "0.075")
(command "_circle" "2877.8625,-40.2693" "0.075")
(command "_circle" "2877.8625,-39.9693" "0.075")
(command "_circle" "2877.8625,-39.6693" "0.075")
(command "_circle" "2877.8625,-39.3693" "0.075")
(command "_circle" "2877.8625,-39.0693" "0.075")
(command "_layer" "set" "nitride" "")
(setq coords (list 
(list 2880.2625 -14.8263) 
(list 2880.2625 100.8184) 
(list 2879.7375 100.8184) 
(list 2879.7375 -14.8263)))
(apply 'command (append '("pline") coords '("c")))
(setq currobj (ssadd (entlast) currobj))
(command "_layer" "set" "prebias" "")
(command "_rectangle" "2879.7375,-14.8263" "2880.2625,100.8184")
(setq currobj (ssadd (entlast) currobj))
(command "_layer" "set" "nitride" "")
(setq coords (list 
(list 2880.2625 100.8184) 
(list 2880.5625 110.8184) 
(list 2880.5625 110.8184) 
(list 2880.5625 111.8184) 
(list 2954.585 111.0684) 
(list 2954.585 116.0114) 
(list 2880.5625 115.2614) 
(list 2880.5625 116.2614) 
(list 2880.5625 116.2614) 
(list 2880.2625 126.2614) 
(list 2879.7375 126.2614) 
(list 2879.4375 116.2614) 
(list 2879.4375 116.2614) 
(list 2879.4375 115.2614) 
(list 2805.415 116.0114) 
(list 2805.415 111.0684) 
(list 2879.4375 111.8184) 
(list 2879.4375 110.8184) 
(list 2879.4375 110.8184) 
(list 2879.7375 100.8184)))
(apply 'command (append '("pline") coords '("c")))
(setq currobj (ssadd (entlast) currobj))
(command "_layer" "set" "prebias" "")
(setq coords (list 
(list 2879.4375 100.8184) 
(list 2879.4375 111.8184) 
(list 2805.415 111.0684) 
(list 2805.415 116.0114) 
(list 2879.4375 115.2614) 
(list 2879.4375 126.2614) 
(list 2880.5625 126.2614) 
(list 2880.5625 115.2614) 
(list 2954.585 116.0114) 
(list 2954.585 111.0684) 
(list 2880.5625 111.8184) 
(list 2880.5625 100.8184)))
(apply 'command (append '("pline") coords '("c")))
(setq currobj (ssadd (entlast) currobj))
(command "_layer" "set" "nitride" "")
(command "_layer" "set" "fda1" "")
(setq coords (list 
(list 2880.5625 111.9614) 
(list 2954.585 111.2114) 
(list 2954.585 111.3884) 
(list 2880.5625 112.0384)))
(apply 'command (append '("pline") coords '("c")))
(setq currobj (ssadd (entlast) currobj))
(setq coords (list 
(list 2880.5625 112.1814) 
(list 2954.585 111.5314) 
(list 2954.585 111.7084) 
(list 2880.5625 112.2584)))
(apply 'command (append '("pline") coords '("c")))
(setq currobj (ssadd (entlast) currobj))
(setq coords (list 
(list 2880.5625 112.4014) 
(list 2954.585 111.8514) 
(list 2954.585 112.0284) 
(list 2880.5625 112.4784)))
(apply 'command (append '("pline") coords '("c")))
(setq currobj (ssadd (entlast) currobj))
(setq coords (list 
(list 2880.5625 112.6214) 
(list 2954.585 112.1714) 
(list 2954.585 112.3484) 
(list 2880.5625 112.6984)))
(apply 'command (append '("pline") coords '("c")))
(setq currobj (ssadd (entlast) currobj))
(setq coords (list 
(list 2880.5625 112.8414) 
(list 2954.585 112.4914) 
(list 2954.585 112.6684) 
(list 2880.5625 112.9184)))
(apply 'command (append '("pline") coords '("c")))
(setq currobj (ssadd (entlast) currobj))
(setq coords (list 
(list 2880.5625 113.0614) 
(list 2954.585 112.8114) 
(list 2954.585 112.9884) 
(list 2880.5625 113.1384)))
(apply 'command (append '("pline") coords '("c")))
(setq currobj (ssadd (entlast) currobj))
(setq coords (list 
(list 2880.5625 113.2814) 
(list 2954.585 113.1314) 
(list 2954.585 113.3084) 
(list 2880.5625 113.3584)))
(apply 'command (append '("pline") coords '("c")))
(setq currobj (ssadd (entlast) currobj))
(setq coords (list 
(list 2880.5625 113.5014) 
(list 2954.585 113.4514) 
(list 2954.585 113.6284) 
(list 2880.5625 113.5784)))
(apply 'command (append '("pline") coords '("c")))
(setq currobj (ssadd (entlast) currobj))
(setq coords (list 
(list 2880.5625 113.7214) 
(list 2954.585 113.7714) 
(list 2954.585 113.9484) 
(list 2880.5625 113.7984)))
(apply 'command (append '("pline") coords '("c")))
(setq currobj (ssadd (entlast) currobj))
(setq coords (list 
(list 2880.5625 113.9414) 
(list 2954.585 114.0914) 
(list 2954.585 114.2684) 
(list 2880.5625 114.0184)))
(apply 'command (append '("pline") coords '("c")))
(setq currobj (ssadd (entlast) currobj))
(setq coords (list 
(list 2880.5625 114.1614) 
(list 2954.585 114.4114) 
(list 2954.585 114.5884) 
(list 2880.5625 114.2384)))
(apply 'command (append '("pline") coords '("c")))
(setq currobj (ssadd (entlast) currobj))
(setq coords (list 
(list 2880.5625 114.3814) 
(list 2954.585 114.7314) 
(list 2954.585 114.9084) 
(list 2880.5625 114.4584)))
(apply 'command (append '("pline") coords '("c")))
(setq currobj (ssadd (entlast) currobj))
(setq coords (list 
(list 2880.5625 114.6014) 
(list 2954.585 115.0514) 
(list 2954.585 115.2284) 
(list 2880.5625 114.6784)))
(apply 'command (append '("pline") coords '("c")))
(setq currobj (ssadd (entlast) currobj))
(setq coords (list 
(list 2880.5625 114.8214) 
(list 2954.585 115.3714) 
(list 2954.585 115.5484) 
(list 2880.5625 114.8984)))
(apply 'command (append '("pline") coords '("c")))
(setq currobj (ssadd (entlast) currobj))
(setq coords (list 
(list 2880.5625 115.0414) 
(list 2954.585 115.6914) 
(list 2954.585 115.8684) 
(list 2880.5625 115.1184)))
(apply 'command (append '("pline") coords '("c")))
(setq currobj (ssadd (entlast) currobj))
(setq coords (list 
(list 2879.4375 115.1184) 
(list 2805.415 115.8684) 
(list 2805.415 115.6914) 
(list 2879.4375 115.0414)))
(apply 'command (append '("pline") coords '("c")))
(setq currobj (ssadd (entlast) currobj))
(setq coords (list 
(list 2879.4375 114.8984) 
(list 2805.415 115.5484) 
(list 2805.415 115.3714) 
(list 2879.4375 114.8214)))
(apply 'command (append '("pline") coords '("c")))
(setq currobj (ssadd (entlast) currobj))
(setq coords (list 
(list 2879.4375 114.6784) 
(list 2805.415 115.2284) 
(list 2805.415 115.0514) 
(list 2879.4375 114.6014)))
(apply 'command (append '("pline") coords '("c")))
(setq currobj (ssadd (entlast) currobj))
(setq coords (list 
(list 2879.4375 114.4584) 
(list 2805.415 114.9084) 
(list 2805.415 114.7314) 
(list 2879.4375 114.3814)))
(apply 'command (append '("pline") coords '("c")))
(setq currobj (ssadd (entlast) currobj))
(setq coords (list 
(list 2879.4375 114.2384) 
(list 2805.415 114.5884) 
(list 2805.415 114.4114) 
(list 2879.4375 114.1614)))
(apply 'command (append '("pline") coords '("c")))
(setq currobj (ssadd (entlast) currobj))
(setq coords (list 
(list 2879.4375 114.0184) 
(list 2805.415 114.2684) 
(list 2805.415 114.0914) 
(list 2879.4375 113.9414)))
(apply 'command (append '("pline") coords '("c")))
(setq currobj (ssadd (entlast) currobj))
(setq coords (list 
(list 2879.4375 113.7984) 
(list 2805.415 113.9484) 
(list 2805.415 113.7714) 
(list 2879.4375 113.7214)))
(apply 'command (append '("pline") coords '("c")))
(setq currobj (ssadd (entlast) currobj))
(setq coords (list 
(list 2879.4375 113.5784) 
(list 2805.415 113.6284) 
(list 2805.415 113.4514) 
(list 2879.4375 113.5014)))
(apply 'command (append '("pline") coords '("c")))
(setq currobj (ssadd (entlast) currobj))
(setq coords (list 
(list 2879.4375 113.3584) 
(list 2805.415 113.3084) 
(list 2805.415 113.1314) 
(list 2879.4375 113.2814)))
(apply 'command (append '("pline") coords '("c")))
(setq currobj (ssadd (entlast) currobj))
(setq coords (list 
(list 2879.4375 113.1384) 
(list 2805.415 112.9884) 
(list 2805.415 112.8114) 
(list 2879.4375 113.0614)))
(apply 'command (append '("pline") coords '("c")))
(setq currobj (ssadd (entlast) currobj))
(setq coords (list 
(list 2879.4375 112.9184) 
(list 2805.415 112.6684) 
(list 2805.415 112.4914) 
(list 2879.4375 112.8414)))
(apply 'command (append '("pline") coords '("c")))
(setq currobj (ssadd (entlast) currobj))
(setq coords (list 
(list 2879.4375 112.6984) 
(list 2805.415 112.3484) 
(list 2805.415 112.1714) 
(list 2879.4375 112.6214)))
(apply 'command (append '("pline") coords '("c")))
(setq currobj (ssadd (entlast) currobj))
(setq coords (list 
(list 2879.4375 112.4784) 
(list 2805.415 112.0284) 
(list 2805.415 111.8514) 
(list 2879.4375 112.4014)))
(apply 'command (append '("pline") coords '("c")))
(setq currobj (ssadd (entlast) currobj))
(setq coords (list 
(list 2879.4375 112.2584) 
(list 2805.415 111.7084) 
(list 2805.415 111.5314) 
(list 2879.4375 112.1814)))
(apply 'command (append '("pline") coords '("c")))
(setq currobj (ssadd (entlast) currobj))
(setq coords (list 
(list 2879.4375 112.0384) 
(list 2805.415 111.3884) 
(list 2805.415 111.2114) 
(list 2879.4375 111.9614)))
(apply 'command (append '("pline") coords '("c")))
(setq currobj (ssadd (entlast) currobj))
(command "_layer" "set" "nitride" "")
(command "_layer" "set" "text" "")
(command "_circle" "2879.0625,100.8184" "0.075")
(command "_circle" "2879.0625,101.1184" "0.075")
(command "_circle" "2879.0625,101.4184" "0.075")
(command "_circle" "2879.0625,101.7184" "0.075")
(command "_circle" "2879.0625,102.0184" "0.075")
(command "_circle" "2878.7625,100.8184" "0.075")
(command "_circle" "2878.7625,101.1184" "0.075")
(command "_circle" "2878.7625,101.4184" "0.075")
(command "_circle" "2878.7625,101.7184" "0.075")
(command "_circle" "2878.7625,102.0184" "0.075")
(command "_circle" "2878.4625,100.8184" "0.075")
(command "_circle" "2878.4625,101.1184" "0.075")
(command "_circle" "2878.4625,101.4184" "0.075")
(command "_circle" "2878.4625,101.7184" "0.075")
(command "_circle" "2878.4625,102.0184" "0.075")
(command "_circle" "2878.1625,100.8184" "0.075")
(command "_circle" "2878.1625,101.1184" "0.075")
(command "_circle" "2878.1625,101.4184" "0.075")
(command "_circle" "2878.1625,101.7184" "0.075")
(command "_circle" "2878.1625,102.0184" "0.075")
(command "_circle" "2877.8625,100.8184" "0.075")
(command "_circle" "2877.8625,101.1184" "0.075")
(command "_circle" "2877.8625,101.4184" "0.075")
(command "_circle" "2877.8625,101.7184" "0.075")
(command "_circle" "2877.8625,102.0184" "0.075")
(command "_layer" "set" "nitride" "")
(setq coords (list 
(list 2880.2625 126.2614) 
(list 2880.2625 241.9061) 
(list 2879.7375 241.9061) 
(list 2879.7375 126.2614)))
(apply 'command (append '("pline") coords '("c")))
(setq currobj (ssadd (entlast) currobj))
(command "_layer" "set" "prebias" "")
(command "_rectangle" "2879.7375,126.2614" "2880.2625,241.9061")
(setq currobj (ssadd (entlast) currobj))
(command "_layer" "set" "nitride" "")
(setq coords (list 
(list 2880.2625 241.9061) 
(list 2880.5625 251.9061) 
(list 2880.5625 251.9061) 
(list 2880.5625 252.9061) 
(list 2954.585 252.1561) 
(list 2954.585 257.0991) 
(list 2880.5625 256.3491) 
(list 2880.5625 257.3491) 
(list 2880.5625 257.3491) 
(list 2880.2625 267.3491) 
(list 2879.7375 267.3491) 
(list 2879.4375 257.3491) 
(list 2879.4375 257.3491) 
(list 2879.4375 256.3491) 
(list 2805.415 257.0991) 
(list 2805.415 252.1561) 
(list 2879.4375 252.9061) 
(list 2879.4375 251.9061) 
(list 2879.4375 251.9061) 
(list 2879.7375 241.9061)))
(apply 'command (append '("pline") coords '("c")))
(setq currobj (ssadd (entlast) currobj))
(command "_layer" "set" "prebias" "")
(setq coords (list 
(list 2879.4375 241.9061) 
(list 2879.4375 252.9061) 
(list 2805.415 252.1561) 
(list 2805.415 257.0991) 
(list 2879.4375 256.3491) 
(list 2879.4375 267.3491) 
(list 2880.5625 267.3491) 
(list 2880.5625 256.3491) 
(list 2954.585 257.0991) 
(list 2954.585 252.1561) 
(list 2880.5625 252.9061) 
(list 2880.5625 241.9061)))
(apply 'command (append '("pline") coords '("c")))
(setq currobj (ssadd (entlast) currobj))
(command "_layer" "set" "nitride" "")
(command "_layer" "set" "fda1" "")
(setq coords (list 
(list 2880.5625 253.0491) 
(list 2954.585 252.2991) 
(list 2954.585 252.4761) 
(list 2880.5625 253.1261)))
(apply 'command (append '("pline") coords '("c")))
(setq currobj (ssadd (entlast) currobj))
(setq coords (list 
(list 2880.5625 253.2691) 
(list 2954.585 252.6191) 
(list 2954.585 252.7961) 
(list 2880.5625 253.3461)))
(apply 'command (append '("pline") coords '("c")))
(setq currobj (ssadd (entlast) currobj))
(setq coords (list 
(list 2880.5625 253.4891) 
(list 2954.585 252.9391) 
(list 2954.585 253.1161) 
(list 2880.5625 253.5661)))
(apply 'command (append '("pline") coords '("c")))
(setq currobj (ssadd (entlast) currobj))
(setq coords (list 
(list 2880.5625 253.7091) 
(list 2954.585 253.2591) 
(list 2954.585 253.4361) 
(list 2880.5625 253.7861)))
(apply 'command (append '("pline") coords '("c")))
(setq currobj (ssadd (entlast) currobj))
(setq coords (list 
(list 2880.5625 253.9291) 
(list 2954.585 253.5791) 
(list 2954.585 253.7561) 
(list 2880.5625 254.0061)))
(apply 'command (append '("pline") coords '("c")))
(setq currobj (ssadd (entlast) currobj))
(setq coords (list 
(list 2880.5625 254.1491) 
(list 2954.585 253.8991) 
(list 2954.585 254.0761) 
(list 2880.5625 254.2261)))
(apply 'command (append '("pline") coords '("c")))
(setq currobj (ssadd (entlast) currobj))
(setq coords (list 
(list 2880.5625 254.3691) 
(list 2954.585 254.2191) 
(list 2954.585 254.3961) 
(list 2880.5625 254.4461)))
(apply 'command (append '("pline") coords '("c")))
(setq currobj (ssadd (entlast) currobj))
(setq coords (list 
(list 2880.5625 254.5891) 
(list 2954.585 254.5391) 
(list 2954.585 254.7161) 
(list 2880.5625 254.6661)))
(apply 'command (append '("pline") coords '("c")))
(setq currobj (ssadd (entlast) currobj))
(setq coords (list 
(list 2880.5625 254.8091) 
(list 2954.585 254.8591) 
(list 2954.585 255.0361) 
(list 2880.5625 254.8861)))
(apply 'command (append '("pline") coords '("c")))
(setq currobj (ssadd (entlast) currobj))
(setq coords (list 
(list 2880.5625 255.0291) 
(list 2954.585 255.1791) 
(list 2954.585 255.3561) 
(list 2880.5625 255.1061)))
(apply 'command (append '("pline") coords '("c")))
(setq currobj (ssadd (entlast) currobj))
(setq coords (list 
(list 2880.5625 255.2491) 
(list 2954.585 255.4991) 
(list 2954.585 255.6761) 
(list 2880.5625 255.3261)))
(apply 'command (append '("pline") coords '("c")))
(setq currobj (ssadd (entlast) currobj))
(setq coords (list 
(list 2880.5625 255.4691) 
(list 2954.585 255.8191) 
(list 2954.585 255.9961) 
(list 2880.5625 255.5461)))
(apply 'command (append '("pline") coords '("c")))
(setq currobj (ssadd (entlast) currobj))
(setq coords (list 
(list 2880.5625 255.6891) 
(list 2954.585 256.1391) 
(list 2954.585 256.3161) 
(list 2880.5625 255.7661)))
(apply 'command (append '("pline") coords '("c")))
(setq currobj (ssadd (entlast) currobj))
(setq coords (list 
(list 2880.5625 255.9091) 
(list 2954.585 256.4591) 
(list 2954.585 256.6361) 
(list 2880.5625 255.9861)))
(apply 'command (append '("pline") coords '("c")))
(setq currobj (ssadd (entlast) currobj))
(setq coords (list 
(list 2880.5625 256.1291) 
(list 2954.585 256.7791) 
(list 2954.585 256.9561) 
(list 2880.5625 256.2061)))
(apply 'command (append '("pline") coords '("c")))
(setq currobj (ssadd (entlast) currobj))
(setq coords (list 
(list 2879.4375 256.2061) 
(list 2805.415 256.9561) 
(list 2805.415 256.7791) 
(list 2879.4375 256.1291)))
(apply 'command (append '("pline") coords '("c")))
(setq currobj (ssadd (entlast) currobj))
(setq coords (list 
(list 2879.4375 255.9861) 
(list 2805.415 256.6361) 
(list 2805.415 256.4591) 
(list 2879.4375 255.9091)))
(apply 'command (append '("pline") coords '("c")))
(setq currobj (ssadd (entlast) currobj))
(setq coords (list 
(list 2879.4375 255.7661) 
(list 2805.415 256.3161) 
(list 2805.415 256.1391) 
(list 2879.4375 255.6891)))
(apply 'command (append '("pline") coords '("c")))
(setq currobj (ssadd (entlast) currobj))
(setq coords (list 
(list 2879.4375 255.5461) 
(list 2805.415 255.9961) 
(list 2805.415 255.8191) 
(list 2879.4375 255.4691)))
(apply 'command (append '("pline") coords '("c")))
(setq currobj (ssadd (entlast) currobj))
(setq coords (list 
(list 2879.4375 255.3261) 
(list 2805.415 255.6761) 
(list 2805.415 255.4991) 
(list 2879.4375 255.2491)))
(apply 'command (append '("pline") coords '("c")))
(setq currobj (ssadd (entlast) currobj))
(setq coords (list 
(list 2879.4375 255.1061) 
(list 2805.415 255.3561) 
(list 2805.415 255.1791) 
(list 2879.4375 255.0291)))
(apply 'command (append '("pline") coords '("c")))
(setq currobj (ssadd (entlast) currobj))
(setq coords (list 
(list 2879.4375 254.8861) 
(list 2805.415 255.0361) 
(list 2805.415 254.8591) 
(list 2879.4375 254.8091)))
(apply 'command (append '("pline") coords '("c")))
(setq currobj (ssadd (entlast) currobj))
(setq coords (list 
(list 2879.4375 254.6661) 
(list 2805.415 254.7161) 
(list 2805.415 254.5391) 
(list 2879.4375 254.5891)))
(apply 'command (append '("pline") coords '("c")))
(setq currobj (ssadd (entlast) currobj))
(setq coords (list 
(list 2879.4375 254.4461) 
(list 2805.415 254.3961) 
(list 2805.415 254.2191) 
(list 2879.4375 254.3691)))
(apply 'command (append '("pline") coords '("c")))
(setq currobj (ssadd (entlast) currobj))
(setq coords (list 
(list 2879.4375 254.2261) 
(list 2805.415 254.0761) 
(list 2805.415 253.8991) 
(list 2879.4375 254.1491)))
(apply 'command (append '("pline") coords '("c")))
(setq currobj (ssadd (entlast) currobj))
(setq coords (list 
(list 2879.4375 254.0061) 
(list 2805.415 253.7561) 
(list 2805.415 253.5791) 
(list 2879.4375 253.9291)))
(apply 'command (append '("pline") coords '("c")))
(setq currobj (ssadd (entlast) currobj))
(setq coords (list 
(list 2879.4375 253.7861) 
(list 2805.415 253.4361) 
(list 2805.415 253.2591) 
(list 2879.4375 253.7091)))
(apply 'command (append '("pline") coords '("c")))
(setq currobj (ssadd (entlast) currobj))
(setq coords (list 
(list 2879.4375 253.5661) 
(list 2805.415 253.1161) 
(list 2805.415 252.9391) 
(list 2879.4375 253.4891)))
(apply 'command (append '("pline") coords '("c")))
(setq currobj (ssadd (entlast) currobj))
(setq coords (list 
(list 2879.4375 253.3461) 
(list 2805.415 252.7961) 
(list 2805.415 252.6191) 
(list 2879.4375 253.2691)))
(apply 'command (append '("pline") coords '("c")))
(setq currobj (ssadd (entlast) currobj))
(setq coords (list 
(list 2879.4375 253.1261) 
(list 2805.415 252.4761) 
(list 2805.415 252.2991) 
(list 2879.4375 253.0491)))
(apply 'command (append '("pline") coords '("c")))
(setq currobj (ssadd (entlast) currobj))
(command "_layer" "set" "nitride" "")
(command "_layer" "set" "text" "")
(command "_circle" "2879.0625,241.9061" "0.075")
(command "_circle" "2879.0625,242.2061" "0.075")
(command "_circle" "2879.0625,242.5061" "0.075")
(command "_circle" "2879.0625,242.8061" "0.075")
(command "_circle" "2879.0625,243.1061" "0.075")
(command "_circle" "2878.7625,241.9061" "0.075")
(command "_circle" "2878.7625,242.2061" "0.075")
(command "_circle" "2878.7625,242.5061" "0.075")
(command "_circle" "2878.7625,242.8061" "0.075")
(command "_circle" "2878.7625,243.1061" "0.075")
(command "_circle" "2878.4625,241.9061" "0.075")
(command "_circle" "2878.4625,242.2061" "0.075")
(command "_circle" "2878.4625,242.5061" "0.075")
(command "_circle" "2878.4625,242.8061" "0.075")
(command "_circle" "2878.4625,243.1061" "0.075")
(command "_circle" "2878.1625,241.9061" "0.075")
(command "_circle" "2878.1625,242.2061" "0.075")
(command "_circle" "2878.1625,242.5061" "0.075")
(command "_circle" "2878.1625,242.8061" "0.075")
(command "_circle" "2878.1625,243.1061" "0.075")
(command "_circle" "2877.8625,241.9061" "0.075")
(command "_circle" "2877.8625,242.2061" "0.075")
(command "_circle" "2877.8625,242.5061" "0.075")
(command "_circle" "2877.8625,242.8061" "0.075")
(command "_circle" "2877.8625,243.1061" "0.075")
(command "_layer" "set" "nitride" "")
(setq coords (list 
(list 2880.2625 267.3491) 
(list 2880.2625 382.9939) 
(list 2879.7375 382.9939) 
(list 2879.7375 267.3491)))
(apply 'command (append '("pline") coords '("c")))
(setq currobj (ssadd (entlast) currobj))
(command "_layer" "set" "prebias" "")
(command "_rectangle" "2879.7375,267.3491" "2880.2625,382.9939")
(setq currobj (ssadd (entlast) currobj))
(command "_layer" "set" "nitride" "")
(setq coords (list 
(list 2880.2625 382.9939) 
(list 2880.5625 392.9939) 
(list 2880.5625 392.9939) 
(list 2880.5625 393.9939) 
(list 2954.585 393.2439) 
(list 2954.585 398.1869) 
(list 2880.5625 397.4369) 
(list 2880.5625 398.4369) 
(list 2880.5625 398.4369) 
(list 2880.2625 408.4369) 
(list 2879.7375 408.4369) 
(list 2879.4375 398.4369) 
(list 2879.4375 398.4369) 
(list 2879.4375 397.4369) 
(list 2805.415 398.1869) 
(list 2805.415 393.2439) 
(list 2879.4375 393.9939) 
(list 2879.4375 392.9939) 
(list 2879.4375 392.9939) 
(list 2879.7375 382.9939)))
(apply 'command (append '("pline") coords '("c")))
(setq currobj (ssadd (entlast) currobj))
(command "_layer" "set" "prebias" "")
(setq coords (list 
(list 2879.4375 382.9939) 
(list 2879.4375 393.9939) 
(list 2805.415 393.2439) 
(list 2805.415 398.1869) 
(list 2879.4375 397.4369) 
(list 2879.4375 408.4369) 
(list 2880.5625 408.4369) 
(list 2880.5625 397.4369) 
(list 2954.585 398.1869) 
(list 2954.585 393.2439) 
(list 2880.5625 393.9939) 
(list 2880.5625 382.9939)))
(apply 'command (append '("pline") coords '("c")))
(setq currobj (ssadd (entlast) currobj))
(command "_layer" "set" "nitride" "")
(command "_layer" "set" "fda1" "")
(setq coords (list 
(list 2880.5625 394.1369) 
(list 2954.585 393.3869) 
(list 2954.585 393.5639) 
(list 2880.5625 394.2139)))
(apply 'command (append '("pline") coords '("c")))
(setq currobj (ssadd (entlast) currobj))
(setq coords (list 
(list 2880.5625 394.3569) 
(list 2954.585 393.7069) 
(list 2954.585 393.8839) 
(list 2880.5625 394.4339)))
(apply 'command (append '("pline") coords '("c")))
(setq currobj (ssadd (entlast) currobj))
(setq coords (list 
(list 2880.5625 394.5769) 
(list 2954.585 394.0269) 
(list 2954.585 394.2039) 
(list 2880.5625 394.6539)))
(apply 'command (append '("pline") coords '("c")))
(setq currobj (ssadd (entlast) currobj))
(setq coords (list 
(list 2880.5625 394.7969) 
(list 2954.585 394.3469) 
(list 2954.585 394.5239) 
(list 2880.5625 394.8739)))
(apply 'command (append '("pline") coords '("c")))
(setq currobj (ssadd (entlast) currobj))
(setq coords (list 
(list 2880.5625 395.0169) 
(list 2954.585 394.6669) 
(list 2954.585 394.8439) 
(list 2880.5625 395.0939)))
(apply 'command (append '("pline") coords '("c")))
(setq currobj (ssadd (entlast) currobj))
(setq coords (list 
(list 2880.5625 395.2369) 
(list 2954.585 394.9869) 
(list 2954.585 395.1639) 
(list 2880.5625 395.3139)))
(apply 'command (append '("pline") coords '("c")))
(setq currobj (ssadd (entlast) currobj))
(setq coords (list 
(list 2880.5625 395.4569) 
(list 2954.585 395.3069) 
(list 2954.585 395.4839) 
(list 2880.5625 395.5339)))
(apply 'command (append '("pline") coords '("c")))
(setq currobj (ssadd (entlast) currobj))
(setq coords (list 
(list 2880.5625 395.6769) 
(list 2954.585 395.6269) 
(list 2954.585 395.8039) 
(list 2880.5625 395.7539)))
(apply 'command (append '("pline") coords '("c")))
(setq currobj (ssadd (entlast) currobj))
(setq coords (list 
(list 2880.5625 395.8969) 
(list 2954.585 395.9469) 
(list 2954.585 396.1239) 
(list 2880.5625 395.9739)))
(apply 'command (append '("pline") coords '("c")))
(setq currobj (ssadd (entlast) currobj))
(setq coords (list 
(list 2880.5625 396.1169) 
(list 2954.585 396.2669) 
(list 2954.585 396.4439) 
(list 2880.5625 396.1939)))
(apply 'command (append '("pline") coords '("c")))
(setq currobj (ssadd (entlast) currobj))
(setq coords (list 
(list 2880.5625 396.3369) 
(list 2954.585 396.5869) 
(list 2954.585 396.7639) 
(list 2880.5625 396.4139)))
(apply 'command (append '("pline") coords '("c")))
(setq currobj (ssadd (entlast) currobj))
(setq coords (list 
(list 2880.5625 396.5569) 
(list 2954.585 396.9069) 
(list 2954.585 397.0839) 
(list 2880.5625 396.6339)))
(apply 'command (append '("pline") coords '("c")))
(setq currobj (ssadd (entlast) currobj))
(setq coords (list 
(list 2880.5625 396.7769) 
(list 2954.585 397.2269) 
(list 2954.585 397.4039) 
(list 2880.5625 396.8539)))
(apply 'command (append '("pline") coords '("c")))
(setq currobj (ssadd (entlast) currobj))
(setq coords (list 
(list 2880.5625 396.9969) 
(list 2954.585 397.5469) 
(list 2954.585 397.7239) 
(list 2880.5625 397.0739)))
(apply 'command (append '("pline") coords '("c")))
(setq currobj (ssadd (entlast) currobj))
(setq coords (list 
(list 2880.5625 397.2169) 
(list 2954.585 397.8669) 
(list 2954.585 398.0439) 
(list 2880.5625 397.2939)))
(apply 'command (append '("pline") coords '("c")))
(setq currobj (ssadd (entlast) currobj))
(setq coords (list 
(list 2879.4375 397.2939) 
(list 2805.415 398.0439) 
(list 2805.415 397.8669) 
(list 2879.4375 397.2169)))
(apply 'command (append '("pline") coords '("c")))
(setq currobj (ssadd (entlast) currobj))
(setq coords (list 
(list 2879.4375 397.0739) 
(list 2805.415 397.7239) 
(list 2805.415 397.5469) 
(list 2879.4375 396.9969)))
(apply 'command (append '("pline") coords '("c")))
(setq currobj (ssadd (entlast) currobj))
(setq coords (list 
(list 2879.4375 396.8539) 
(list 2805.415 397.4039) 
(list 2805.415 397.2269) 
(list 2879.4375 396.7769)))
(apply 'command (append '("pline") coords '("c")))
(setq currobj (ssadd (entlast) currobj))
(setq coords (list 
(list 2879.4375 396.6339) 
(list 2805.415 397.0839) 
(list 2805.415 396.9069) 
(list 2879.4375 396.5569)))
(apply 'command (append '("pline") coords '("c")))
(setq currobj (ssadd (entlast) currobj))
(setq coords (list 
(list 2879.4375 396.4139) 
(list 2805.415 396.7639) 
(list 2805.415 396.5869) 
(list 2879.4375 396.3369)))
(apply 'command (append '("pline") coords '("c")))
(setq currobj (ssadd (entlast) currobj))
(setq coords (list 
(list 2879.4375 396.1939) 
(list 2805.415 396.4439) 
(list 2805.415 396.2669) 
(list 2879.4375 396.1169)))
(apply 'command (append '("pline") coords '("c")))
(setq currobj (ssadd (entlast) currobj))
(setq coords (list 
(list 2879.4375 395.9739) 
(list 2805.415 396.1239) 
(list 2805.415 395.9469) 
(list 2879.4375 395.8969)))
(apply 'command (append '("pline") coords '("c")))
(setq currobj (ssadd (entlast) currobj))
(setq coords (list 
(list 2879.4375 395.7539) 
(list 2805.415 395.8039) 
(list 2805.415 395.6269) 
(list 2879.4375 395.6769)))
(apply 'command (append '("pline") coords '("c")))
(setq currobj (ssadd (entlast) currobj))
(setq coords (list 
(list 2879.4375 395.5339) 
(list 2805.415 395.4839) 
(list 2805.415 395.3069) 
(list 2879.4375 395.4569)))
(apply 'command (append '("pline") coords '("c")))
(setq currobj (ssadd (entlast) currobj))
(setq coords (list 
(list 2879.4375 395.3139) 
(list 2805.415 395.1639) 
(list 2805.415 394.9869) 
(list 2879.4375 395.2369)))
(apply 'command (append '("pline") coords '("c")))
(setq currobj (ssadd (entlast) currobj))
(setq coords (list 
(list 2879.4375 395.0939) 
(list 2805.415 394.8439) 
(list 2805.415 394.6669) 
(list 2879.4375 395.0169)))
(apply 'command (append '("pline") coords '("c")))
(setq currobj (ssadd (entlast) currobj))
(setq coords (list 
(list 2879.4375 394.8739) 
(list 2805.415 394.5239) 
(list 2805.415 394.3469) 
(list 2879.4375 394.7969)))
(apply 'command (append '("pline") coords '("c")))
(setq currobj (ssadd (entlast) currobj))
(setq coords (list 
(list 2879.4375 394.6539) 
(list 2805.415 394.2039) 
(list 2805.415 394.0269) 
(list 2879.4375 394.5769)))
(apply 'command (append '("pline") coords '("c")))
(setq currobj (ssadd (entlast) currobj))
(setq coords (list 
(list 2879.4375 394.4339) 
(list 2805.415 393.8839) 
(list 2805.415 393.7069) 
(list 2879.4375 394.3569)))
(apply 'command (append '("pline") coords '("c")))
(setq currobj (ssadd (entlast) currobj))
(setq coords (list 
(list 2879.4375 394.2139) 
(list 2805.415 393.5639) 
(list 2805.415 393.3869) 
(list 2879.4375 394.1369)))
(apply 'command (append '("pline") coords '("c")))
(setq currobj (ssadd (entlast) currobj))
(command "_layer" "set" "nitride" "")
(command "_layer" "set" "text" "")
(command "_circle" "2879.0625,382.9939" "0.075")
(command "_circle" "2879.0625,383.2939" "0.075")
(command "_circle" "2879.0625,383.5939" "0.075")
(command "_circle" "2879.0625,383.8939" "0.075")
(command "_circle" "2879.0625,384.1939" "0.075")
(command "_circle" "2878.7625,382.9939" "0.075")
(command "_circle" "2878.7625,383.2939" "0.075")
(command "_circle" "2878.7625,383.5939" "0.075")
(command "_circle" "2878.7625,383.8939" "0.075")
(command "_circle" "2878.7625,384.1939" "0.075")
(command "_circle" "2878.4625,382.9939" "0.075")
(command "_circle" "2878.4625,383.2939" "0.075")
(command "_circle" "2878.4625,383.5939" "0.075")
(command "_circle" "2878.4625,383.8939" "0.075")
(command "_circle" "2878.4625,384.1939" "0.075")
(command "_circle" "2878.1625,382.9939" "0.075")
(command "_circle" "2878.1625,383.2939" "0.075")
(command "_circle" "2878.1625,383.5939" "0.075")
(command "_circle" "2878.1625,383.8939" "0.075")
(command "_circle" "2878.1625,384.1939" "0.075")
(command "_circle" "2877.8625,382.9939" "0.075")
(command "_circle" "2877.8625,383.2939" "0.075")
(command "_circle" "2877.8625,383.5939" "0.075")
(command "_circle" "2877.8625,383.8939" "0.075")
(command "_circle" "2877.8625,384.1939" "0.075")
(command "_layer" "set" "nitride" "")
(setq coords (list 
(list 2880.2625 408.4369) 
(list 2880.2625 524.0816) 
(list 2879.7375 524.0816) 
(list 2879.7375 408.4369)))
(apply 'command (append '("pline") coords '("c")))
(setq currobj (ssadd (entlast) currobj))
(command "_layer" "set" "prebias" "")
(command "_rectangle" "2879.7375,408.4369" "2880.2625,524.0816")
(setq currobj (ssadd (entlast) currobj))
(command "_layer" "set" "nitride" "")
(setq coords (list 
(list 2880.2625 524.0816) 
(list 2880.5625 534.0816) 
(list 2880.5625 534.0816) 
(list 2880.5625 535.0816) 
(list 2954.585 534.3316) 
(list 2954.585 539.2746) 
(list 2880.5625 538.5246) 
(list 2880.5625 539.5246) 
(list 2880.5625 539.5246) 
(list 2880.2625 549.5246) 
(list 2879.7375 549.5246) 
(list 2879.4375 539.5246) 
(list 2879.4375 539.5246) 
(list 2879.4375 538.5246) 
(list 2805.415 539.2746) 
(list 2805.415 534.3316) 
(list 2879.4375 535.0816) 
(list 2879.4375 534.0816) 
(list 2879.4375 534.0816) 
(list 2879.7375 524.0816)))
(apply 'command (append '("pline") coords '("c")))
(setq currobj (ssadd (entlast) currobj))
(command "_layer" "set" "prebias" "")
(setq coords (list 
(list 2879.4375 524.0816) 
(list 2879.4375 535.0816) 
(list 2805.415 534.3316) 
(list 2805.415 539.2746) 
(list 2879.4375 538.5246) 
(list 2879.4375 549.5246) 
(list 2880.5625 549.5246) 
(list 2880.5625 538.5246) 
(list 2954.585 539.2746) 
(list 2954.585 534.3316) 
(list 2880.5625 535.0816) 
(list 2880.5625 524.0816)))
(apply 'command (append '("pline") coords '("c")))
(setq currobj (ssadd (entlast) currobj))
(command "_layer" "set" "nitride" "")
(command "_layer" "set" "fda1" "")
(setq coords (list 
(list 2880.5625 535.2246) 
(list 2954.585 534.4746) 
(list 2954.585 534.6516) 
(list 2880.5625 535.3016)))
(apply 'command (append '("pline") coords '("c")))
(setq currobj (ssadd (entlast) currobj))
(setq coords (list 
(list 2880.5625 535.4446) 
(list 2954.585 534.7946) 
(list 2954.585 534.9716) 
(list 2880.5625 535.5216)))
(apply 'command (append '("pline") coords '("c")))
(setq currobj (ssadd (entlast) currobj))
(setq coords (list 
(list 2880.5625 535.6646) 
(list 2954.585 535.1146) 
(list 2954.585 535.2916) 
(list 2880.5625 535.7416)))
(apply 'command (append '("pline") coords '("c")))
(setq currobj (ssadd (entlast) currobj))
(setq coords (list 
(list 2880.5625 535.8846) 
(list 2954.585 535.4346) 
(list 2954.585 535.6116) 
(list 2880.5625 535.9616)))
(apply 'command (append '("pline") coords '("c")))
(setq currobj (ssadd (entlast) currobj))
(setq coords (list 
(list 2880.5625 536.1046) 
(list 2954.585 535.7546) 
(list 2954.585 535.9316) 
(list 2880.5625 536.1816)))
(apply 'command (append '("pline") coords '("c")))
(setq currobj (ssadd (entlast) currobj))
(setq coords (list 
(list 2880.5625 536.3246) 
(list 2954.585 536.0746) 
(list 2954.585 536.2516) 
(list 2880.5625 536.4016)))
(apply 'command (append '("pline") coords '("c")))
(setq currobj (ssadd (entlast) currobj))
(setq coords (list 
(list 2880.5625 536.5446) 
(list 2954.585 536.3946) 
(list 2954.585 536.5716) 
(list 2880.5625 536.6216)))
(apply 'command (append '("pline") coords '("c")))
(setq currobj (ssadd (entlast) currobj))
(setq coords (list 
(list 2880.5625 536.7646) 
(list 2954.585 536.7146) 
(list 2954.585 536.8916) 
(list 2880.5625 536.8416)))
(apply 'command (append '("pline") coords '("c")))
(setq currobj (ssadd (entlast) currobj))
(setq coords (list 
(list 2880.5625 536.9846) 
(list 2954.585 537.0346) 
(list 2954.585 537.2116) 
(list 2880.5625 537.0616)))
(apply 'command (append '("pline") coords '("c")))
(setq currobj (ssadd (entlast) currobj))
(setq coords (list 
(list 2880.5625 537.2046) 
(list 2954.585 537.3546) 
(list 2954.585 537.5316) 
(list 2880.5625 537.2816)))
(apply 'command (append '("pline") coords '("c")))
(setq currobj (ssadd (entlast) currobj))
(setq coords (list 
(list 2880.5625 537.4246) 
(list 2954.585 537.6746) 
(list 2954.585 537.8516) 
(list 2880.5625 537.5016)))
(apply 'command (append '("pline") coords '("c")))
(setq currobj (ssadd (entlast) currobj))
(setq coords (list 
(list 2880.5625 537.6446) 
(list 2954.585 537.9946) 
(list 2954.585 538.1716) 
(list 2880.5625 537.7216)))
(apply 'command (append '("pline") coords '("c")))
(setq currobj (ssadd (entlast) currobj))
(setq coords (list 
(list 2880.5625 537.8646) 
(list 2954.585 538.3146) 
(list 2954.585 538.4916) 
(list 2880.5625 537.9416)))
(apply 'command (append '("pline") coords '("c")))
(setq currobj (ssadd (entlast) currobj))
(setq coords (list 
(list 2880.5625 538.0846) 
(list 2954.585 538.6346) 
(list 2954.585 538.8116) 
(list 2880.5625 538.1616)))
(apply 'command (append '("pline") coords '("c")))
(setq currobj (ssadd (entlast) currobj))
(setq coords (list 
(list 2880.5625 538.3046) 
(list 2954.585 538.9546) 
(list 2954.585 539.1316) 
(list 2880.5625 538.3816)))
(apply 'command (append '("pline") coords '("c")))
(setq currobj (ssadd (entlast) currobj))
(setq coords (list 
(list 2879.4375 538.3816) 
(list 2805.415 539.1316) 
(list 2805.415 538.9546) 
(list 2879.4375 538.3046)))
(apply 'command (append '("pline") coords '("c")))
(setq currobj (ssadd (entlast) currobj))
(setq coords (list 
(list 2879.4375 538.1616) 
(list 2805.415 538.8116) 
(list 2805.415 538.6346) 
(list 2879.4375 538.0846)))
(apply 'command (append '("pline") coords '("c")))
(setq currobj (ssadd (entlast) currobj))
(setq coords (list 
(list 2879.4375 537.9416) 
(list 2805.415 538.4916) 
(list 2805.415 538.3146) 
(list 2879.4375 537.8646)))
(apply 'command (append '("pline") coords '("c")))
(setq currobj (ssadd (entlast) currobj))
(setq coords (list 
(list 2879.4375 537.7216) 
(list 2805.415 538.1716) 
(list 2805.415 537.9946) 
(list 2879.4375 537.6446)))
(apply 'command (append '("pline") coords '("c")))
(setq currobj (ssadd (entlast) currobj))
(setq coords (list 
(list 2879.4375 537.5016) 
(list 2805.415 537.8516) 
(list 2805.415 537.6746) 
(list 2879.4375 537.4246)))
(apply 'command (append '("pline") coords '("c")))
(setq currobj (ssadd (entlast) currobj))
(setq coords (list 
(list 2879.4375 537.2816) 
(list 2805.415 537.5316) 
(list 2805.415 537.3546) 
(list 2879.4375 537.2046)))
(apply 'command (append '("pline") coords '("c")))
(setq currobj (ssadd (entlast) currobj))
(setq coords (list 
(list 2879.4375 537.0616) 
(list 2805.415 537.2116) 
(list 2805.415 537.0346) 
(list 2879.4375 536.9846)))
(apply 'command (append '("pline") coords '("c")))
(setq currobj (ssadd (entlast) currobj))
(setq coords (list 
(list 2879.4375 536.8416) 
(list 2805.415 536.8916) 
(list 2805.415 536.7146) 
(list 2879.4375 536.7646)))
(apply 'command (append '("pline") coords '("c")))
(setq currobj (ssadd (entlast) currobj))
(setq coords (list 
(list 2879.4375 536.6216) 
(list 2805.415 536.5716) 
(list 2805.415 536.3946) 
(list 2879.4375 536.5446)))
(apply 'command (append '("pline") coords '("c")))
(setq currobj (ssadd (entlast) currobj))
(setq coords (list 
(list 2879.4375 536.4016) 
(list 2805.415 536.2516) 
(list 2805.415 536.0746) 
(list 2879.4375 536.3246)))
(apply 'command (append '("pline") coords '("c")))
(setq currobj (ssadd (entlast) currobj))
(setq coords (list 
(list 2879.4375 536.1816) 
(list 2805.415 535.9316) 
(list 2805.415 535.7546) 
(list 2879.4375 536.1046)))
(apply 'command (append '("pline") coords '("c")))
(setq currobj (ssadd (entlast) currobj))
(setq coords (list 
(list 2879.4375 535.9616) 
(list 2805.415 535.6116) 
(list 2805.415 535.4346) 
(list 2879.4375 535.8846)))
(apply 'command (append '("pline") coords '("c")))
(setq currobj (ssadd (entlast) currobj))
(setq coords (list 
(list 2879.4375 535.7416) 
(list 2805.415 535.2916) 
(list 2805.415 535.1146) 
(list 2879.4375 535.6646)))
(apply 'command (append '("pline") coords '("c")))
(setq currobj (ssadd (entlast) currobj))
(setq coords (list 
(list 2879.4375 535.5216) 
(list 2805.415 534.9716) 
(list 2805.415 534.7946) 
(list 2879.4375 535.4446)))
(apply 'command (append '("pline") coords '("c")))
(setq currobj (ssadd (entlast) currobj))
(setq coords (list 
(list 2879.4375 535.3016) 
(list 2805.415 534.6516) 
(list 2805.415 534.4746) 
(list 2879.4375 535.2246)))
(apply 'command (append '("pline") coords '("c")))
(setq currobj (ssadd (entlast) currobj))
(command "_layer" "set" "nitride" "")
(command "_layer" "set" "text" "")
(command "_circle" "2879.0625,524.0816" "0.075")
(command "_circle" "2879.0625,524.3816" "0.075")
(command "_circle" "2879.0625,524.6816" "0.075")
(command "_circle" "2879.0625,524.9816" "0.075")
(command "_circle" "2879.0625,525.2816" "0.075")
(command "_circle" "2878.7625,524.0816" "0.075")
(command "_circle" "2878.7625,524.3816" "0.075")
(command "_circle" "2878.7625,524.6816" "0.075")
(command "_circle" "2878.7625,524.9816" "0.075")
(command "_circle" "2878.7625,525.2816" "0.075")
(command "_circle" "2878.4625,524.0816" "0.075")
(command "_circle" "2878.4625,524.3816" "0.075")
(command "_circle" "2878.4625,524.6816" "0.075")
(command "_circle" "2878.4625,524.9816" "0.075")
(command "_circle" "2878.4625,525.2816" "0.075")
(command "_circle" "2878.1625,524.0816" "0.075")
(command "_circle" "2878.1625,524.3816" "0.075")
(command "_circle" "2878.1625,524.6816" "0.075")
(command "_circle" "2878.1625,524.9816" "0.075")
(command "_circle" "2878.1625,525.2816" "0.075")
(command "_circle" "2877.8625,524.0816" "0.075")
(command "_circle" "2877.8625,524.3816" "0.075")
(command "_circle" "2877.8625,524.6816" "0.075")
(command "_circle" "2877.8625,524.9816" "0.075")
(command "_circle" "2877.8625,525.2816" "0.075")
(command "_layer" "set" "nitride" "")
(setq coords (list 
(list 2880.2625 549.5246) 
(list 2880.2625 665.1693) 
(list 2879.7375 665.1693) 
(list 2879.7375 549.5246)))
(apply 'command (append '("pline") coords '("c")))
(setq currobj (ssadd (entlast) currobj))
(command "_layer" "set" "prebias" "")
(command "_rectangle" "2879.7375,549.5246" "2880.2625,665.1693")
(setq currobj (ssadd (entlast) currobj))
(command "_layer" "set" "nitride" "")
(setq coords (list 
(list 2880.2625 665.1693) 
(list 2880.5625 675.1693) 
(list 2880.5625 675.1693) 
(list 2880.5625 676.1693) 
(list 2954.585 675.4193) 
(list 2954.585 680.3623) 
(list 2880.5625 679.6123) 
(list 2880.5625 680.6123) 
(list 2880.5625 680.6123) 
(list 2880.2625 690.6123) 
(list 2879.7375 690.6123) 
(list 2879.4375 680.6123) 
(list 2879.4375 680.6123) 
(list 2879.4375 679.6123) 
(list 2805.415 680.3623) 
(list 2805.415 675.4193) 
(list 2879.4375 676.1693) 
(list 2879.4375 675.1693) 
(list 2879.4375 675.1693) 
(list 2879.7375 665.1693)))
(apply 'command (append '("pline") coords '("c")))
(setq currobj (ssadd (entlast) currobj))
(command "_layer" "set" "prebias" "")
(setq coords (list 
(list 2879.4375 665.1693) 
(list 2879.4375 676.1693) 
(list 2805.415 675.4193) 
(list 2805.415 680.3623) 
(list 2879.4375 679.6123) 
(list 2879.4375 690.6123) 
(list 2880.5625 690.6123) 
(list 2880.5625 679.6123) 
(list 2954.585 680.3623) 
(list 2954.585 675.4193) 
(list 2880.5625 676.1693) 
(list 2880.5625 665.1693)))
(apply 'command (append '("pline") coords '("c")))
(setq currobj (ssadd (entlast) currobj))
(command "_layer" "set" "nitride" "")
(command "_layer" "set" "fda1" "")
(setq coords (list 
(list 2880.5625 676.3123) 
(list 2954.585 675.5623) 
(list 2954.585 675.7393) 
(list 2880.5625 676.3893)))
(apply 'command (append '("pline") coords '("c")))
(setq currobj (ssadd (entlast) currobj))
(setq coords (list 
(list 2880.5625 676.5323) 
(list 2954.585 675.8823) 
(list 2954.585 676.0593) 
(list 2880.5625 676.6093)))
(apply 'command (append '("pline") coords '("c")))
(setq currobj (ssadd (entlast) currobj))
(setq coords (list 
(list 2880.5625 676.7523) 
(list 2954.585 676.2023) 
(list 2954.585 676.3793) 
(list 2880.5625 676.8293)))
(apply 'command (append '("pline") coords '("c")))
(setq currobj (ssadd (entlast) currobj))
(setq coords (list 
(list 2880.5625 676.9723) 
(list 2954.585 676.5223) 
(list 2954.585 676.6993) 
(list 2880.5625 677.0493)))
(apply 'command (append '("pline") coords '("c")))
(setq currobj (ssadd (entlast) currobj))
(setq coords (list 
(list 2880.5625 677.1923) 
(list 2954.585 676.8423) 
(list 2954.585 677.0193) 
(list 2880.5625 677.2693)))
(apply 'command (append '("pline") coords '("c")))
(setq currobj (ssadd (entlast) currobj))
(setq coords (list 
(list 2880.5625 677.4123) 
(list 2954.585 677.1623) 
(list 2954.585 677.3393) 
(list 2880.5625 677.4893)))
(apply 'command (append '("pline") coords '("c")))
(setq currobj (ssadd (entlast) currobj))
(setq coords (list 
(list 2880.5625 677.6323) 
(list 2954.585 677.4823) 
(list 2954.585 677.6593) 
(list 2880.5625 677.7093)))
(apply 'command (append '("pline") coords '("c")))
(setq currobj (ssadd (entlast) currobj))
(setq coords (list 
(list 2880.5625 677.8523) 
(list 2954.585 677.8023) 
(list 2954.585 677.9793) 
(list 2880.5625 677.9293)))
(apply 'command (append '("pline") coords '("c")))
(setq currobj (ssadd (entlast) currobj))
(setq coords (list 
(list 2880.5625 678.0723) 
(list 2954.585 678.1223) 
(list 2954.585 678.2993) 
(list 2880.5625 678.1493)))
(apply 'command (append '("pline") coords '("c")))
(setq currobj (ssadd (entlast) currobj))
(setq coords (list 
(list 2880.5625 678.2923) 
(list 2954.585 678.4423) 
(list 2954.585 678.6193) 
(list 2880.5625 678.3693)))
(apply 'command (append '("pline") coords '("c")))
(setq currobj (ssadd (entlast) currobj))
(setq coords (list 
(list 2880.5625 678.5123) 
(list 2954.585 678.7623) 
(list 2954.585 678.9393) 
(list 2880.5625 678.5893)))
(apply 'command (append '("pline") coords '("c")))
(setq currobj (ssadd (entlast) currobj))
(setq coords (list 
(list 2880.5625 678.7323) 
(list 2954.585 679.0823) 
(list 2954.585 679.2593) 
(list 2880.5625 678.8093)))
(apply 'command (append '("pline") coords '("c")))
(setq currobj (ssadd (entlast) currobj))
(setq coords (list 
(list 2880.5625 678.9523) 
(list 2954.585 679.4023) 
(list 2954.585 679.5793) 
(list 2880.5625 679.0293)))
(apply 'command (append '("pline") coords '("c")))
(setq currobj (ssadd (entlast) currobj))
(setq coords (list 
(list 2880.5625 679.1723) 
(list 2954.585 679.7223) 
(list 2954.585 679.8993) 
(list 2880.5625 679.2493)))
(apply 'command (append '("pline") coords '("c")))
(setq currobj (ssadd (entlast) currobj))
(setq coords (list 
(list 2880.5625 679.3923) 
(list 2954.585 680.0423) 
(list 2954.585 680.2193) 
(list 2880.5625 679.4693)))
(apply 'command (append '("pline") coords '("c")))
(setq currobj (ssadd (entlast) currobj))
(setq coords (list 
(list 2879.4375 679.4693) 
(list 2805.415 680.2193) 
(list 2805.415 680.0423) 
(list 2879.4375 679.3923)))
(apply 'command (append '("pline") coords '("c")))
(setq currobj (ssadd (entlast) currobj))
(setq coords (list 
(list 2879.4375 679.2493) 
(list 2805.415 679.8993) 
(list 2805.415 679.7223) 
(list 2879.4375 679.1723)))
(apply 'command (append '("pline") coords '("c")))
(setq currobj (ssadd (entlast) currobj))
(setq coords (list 
(list 2879.4375 679.0293) 
(list 2805.415 679.5793) 
(list 2805.415 679.4023) 
(list 2879.4375 678.9523)))
(apply 'command (append '("pline") coords '("c")))
(setq currobj (ssadd (entlast) currobj))
(setq coords (list 
(list 2879.4375 678.8093) 
(list 2805.415 679.2593) 
(list 2805.415 679.0823) 
(list 2879.4375 678.7323)))
(apply 'command (append '("pline") coords '("c")))
(setq currobj (ssadd (entlast) currobj))
(setq coords (list 
(list 2879.4375 678.5893) 
(list 2805.415 678.9393) 
(list 2805.415 678.7623) 
(list 2879.4375 678.5123)))
(apply 'command (append '("pline") coords '("c")))
(setq currobj (ssadd (entlast) currobj))
(setq coords (list 
(list 2879.4375 678.3693) 
(list 2805.415 678.6193) 
(list 2805.415 678.4423) 
(list 2879.4375 678.2923)))
(apply 'command (append '("pline") coords '("c")))
(setq currobj (ssadd (entlast) currobj))
(setq coords (list 
(list 2879.4375 678.1493) 
(list 2805.415 678.2993) 
(list 2805.415 678.1223) 
(list 2879.4375 678.0723)))
(apply 'command (append '("pline") coords '("c")))
(setq currobj (ssadd (entlast) currobj))
(setq coords (list 
(list 2879.4375 677.9293) 
(list 2805.415 677.9793) 
(list 2805.415 677.8023) 
(list 2879.4375 677.8523)))
(apply 'command (append '("pline") coords '("c")))
(setq currobj (ssadd (entlast) currobj))
(setq coords (list 
(list 2879.4375 677.7093) 
(list 2805.415 677.6593) 
(list 2805.415 677.4823) 
(list 2879.4375 677.6323)))
(apply 'command (append '("pline") coords '("c")))
(setq currobj (ssadd (entlast) currobj))
(setq coords (list 
(list 2879.4375 677.4893) 
(list 2805.415 677.3393) 
(list 2805.415 677.1623) 
(list 2879.4375 677.4123)))
(apply 'command (append '("pline") coords '("c")))
(setq currobj (ssadd (entlast) currobj))
(setq coords (list 
(list 2879.4375 677.2693) 
(list 2805.415 677.0193) 
(list 2805.415 676.8423) 
(list 2879.4375 677.1923)))
(apply 'command (append '("pline") coords '("c")))
(setq currobj (ssadd (entlast) currobj))
(setq coords (list 
(list 2879.4375 677.0493) 
(list 2805.415 676.6993) 
(list 2805.415 676.5223) 
(list 2879.4375 676.9723)))
(apply 'command (append '("pline") coords '("c")))
(setq currobj (ssadd (entlast) currobj))
(setq coords (list 
(list 2879.4375 676.8293) 
(list 2805.415 676.3793) 
(list 2805.415 676.2023) 
(list 2879.4375 676.7523)))
(apply 'command (append '("pline") coords '("c")))
(setq currobj (ssadd (entlast) currobj))
(setq coords (list 
(list 2879.4375 676.6093) 
(list 2805.415 676.0593) 
(list 2805.415 675.8823) 
(list 2879.4375 676.5323)))
(apply 'command (append '("pline") coords '("c")))
(setq currobj (ssadd (entlast) currobj))
(setq coords (list 
(list 2879.4375 676.3893) 
(list 2805.415 675.7393) 
(list 2805.415 675.5623) 
(list 2879.4375 676.3123)))
(apply 'command (append '("pline") coords '("c")))
(setq currobj (ssadd (entlast) currobj))
(command "_layer" "set" "nitride" "")
(command "_layer" "set" "text" "")
(command "_circle" "2879.0625,665.1693" "0.075")
(command "_circle" "2879.0625,665.4693" "0.075")
(command "_circle" "2879.0625,665.7693" "0.075")
(command "_circle" "2879.0625,666.0693" "0.075")
(command "_circle" "2879.0625,666.3693" "0.075")
(command "_circle" "2878.7625,665.1693" "0.075")
(command "_circle" "2878.7625,665.4693" "0.075")
(command "_circle" "2878.7625,665.7693" "0.075")
(command "_circle" "2878.7625,666.0693" "0.075")
(command "_circle" "2878.7625,666.3693" "0.075")
(command "_circle" "2878.4625,665.1693" "0.075")
(command "_circle" "2878.4625,665.4693" "0.075")
(command "_circle" "2878.4625,665.7693" "0.075")
(command "_circle" "2878.4625,666.0693" "0.075")
(command "_circle" "2878.4625,666.3693" "0.075")
(command "_circle" "2878.1625,665.1693" "0.075")
(command "_circle" "2878.1625,665.4693" "0.075")
(command "_circle" "2878.1625,665.7693" "0.075")
(command "_circle" "2878.1625,666.0693" "0.075")
(command "_circle" "2878.1625,666.3693" "0.075")
(command "_circle" "2877.8625,665.1693" "0.075")
(command "_circle" "2877.8625,665.4693" "0.075")
(command "_circle" "2877.8625,665.7693" "0.075")
(command "_circle" "2877.8625,666.0693" "0.075")
(command "_circle" "2877.8625,666.3693" "0.075")
(command "_layer" "set" "nitride" "")
(setq coords (list 
(list 2880.2625 690.6123) 
(list 2880.2625 806.257) 
(list 2879.7375 806.257) 
(list 2879.7375 690.6123)))
(apply 'command (append '("pline") coords '("c")))
(setq currobj (ssadd (entlast) currobj))
(command "_layer" "set" "prebias" "")
(command "_rectangle" "2879.7375,690.6123" "2880.2625,806.257")
(setq currobj (ssadd (entlast) currobj))
(command "_layer" "set" "nitride" "")
(setq coords (list 
(list 2880.2625 806.257) 
(list 2880.5625 816.257) 
(list 2880.5625 816.257) 
(list 2880.5625 817.257) 
(list 2954.585 816.507) 
(list 2954.585 821.45) 
(list 2880.5625 820.7) 
(list 2880.5625 821.7) 
(list 2880.5625 821.7) 
(list 2880.2625 831.7) 
(list 2879.7375 831.7) 
(list 2879.4375 821.7) 
(list 2879.4375 821.7) 
(list 2879.4375 820.7) 
(list 2805.415 821.45) 
(list 2805.415 816.507) 
(list 2879.4375 817.257) 
(list 2879.4375 816.257) 
(list 2879.4375 816.257) 
(list 2879.7375 806.257)))
(apply 'command (append '("pline") coords '("c")))
(setq currobj (ssadd (entlast) currobj))
(command "_layer" "set" "prebias" "")
(setq coords (list 
(list 2879.4375 806.257) 
(list 2879.4375 817.257) 
(list 2805.415 816.507) 
(list 2805.415 821.45) 
(list 2879.4375 820.7) 
(list 2879.4375 831.7) 
(list 2880.5625 831.7) 
(list 2880.5625 820.7) 
(list 2954.585 821.45) 
(list 2954.585 816.507) 
(list 2880.5625 817.257) 
(list 2880.5625 806.257)))
(apply 'command (append '("pline") coords '("c")))
(setq currobj (ssadd (entlast) currobj))
(command "_layer" "set" "nitride" "")
(command "_layer" "set" "fda1" "")
(setq coords (list 
(list 2880.5625 817.4) 
(list 2954.585 816.65) 
(list 2954.585 816.827) 
(list 2880.5625 817.477)))
(apply 'command (append '("pline") coords '("c")))
(setq currobj (ssadd (entlast) currobj))
(setq coords (list 
(list 2880.5625 817.62) 
(list 2954.585 816.97) 
(list 2954.585 817.147) 
(list 2880.5625 817.697)))
(apply 'command (append '("pline") coords '("c")))
(setq currobj (ssadd (entlast) currobj))
(setq coords (list 
(list 2880.5625 817.84) 
(list 2954.585 817.29) 
(list 2954.585 817.467) 
(list 2880.5625 817.917)))
(apply 'command (append '("pline") coords '("c")))
(setq currobj (ssadd (entlast) currobj))
(setq coords (list 
(list 2880.5625 818.06) 
(list 2954.585 817.61) 
(list 2954.585 817.787) 
(list 2880.5625 818.137)))
(apply 'command (append '("pline") coords '("c")))
(setq currobj (ssadd (entlast) currobj))
(setq coords (list 
(list 2880.5625 818.28) 
(list 2954.585 817.93) 
(list 2954.585 818.107) 
(list 2880.5625 818.357)))
(apply 'command (append '("pline") coords '("c")))
(setq currobj (ssadd (entlast) currobj))
(setq coords (list 
(list 2880.5625 818.5) 
(list 2954.585 818.25) 
(list 2954.585 818.427) 
(list 2880.5625 818.577)))
(apply 'command (append '("pline") coords '("c")))
(setq currobj (ssadd (entlast) currobj))
(setq coords (list 
(list 2880.5625 818.72) 
(list 2954.585 818.57) 
(list 2954.585 818.747) 
(list 2880.5625 818.797)))
(apply 'command (append '("pline") coords '("c")))
(setq currobj (ssadd (entlast) currobj))
(setq coords (list 
(list 2880.5625 818.94) 
(list 2954.585 818.89) 
(list 2954.585 819.067) 
(list 2880.5625 819.017)))
(apply 'command (append '("pline") coords '("c")))
(setq currobj (ssadd (entlast) currobj))
(setq coords (list 
(list 2880.5625 819.16) 
(list 2954.585 819.21) 
(list 2954.585 819.387) 
(list 2880.5625 819.237)))
(apply 'command (append '("pline") coords '("c")))
(setq currobj (ssadd (entlast) currobj))
(setq coords (list 
(list 2880.5625 819.38) 
(list 2954.585 819.53) 
(list 2954.585 819.707) 
(list 2880.5625 819.457)))
(apply 'command (append '("pline") coords '("c")))
(setq currobj (ssadd (entlast) currobj))
(setq coords (list 
(list 2880.5625 819.6) 
(list 2954.585 819.85) 
(list 2954.585 820.027) 
(list 2880.5625 819.677)))
(apply 'command (append '("pline") coords '("c")))
(setq currobj (ssadd (entlast) currobj))
(setq coords (list 
(list 2880.5625 819.82) 
(list 2954.585 820.17) 
(list 2954.585 820.347) 
(list 2880.5625 819.897)))
(apply 'command (append '("pline") coords '("c")))
(setq currobj (ssadd (entlast) currobj))
(setq coords (list 
(list 2880.5625 820.04) 
(list 2954.585 820.49) 
(list 2954.585 820.667) 
(list 2880.5625 820.117)))
(apply 'command (append '("pline") coords '("c")))
(setq currobj (ssadd (entlast) currobj))
(setq coords (list 
(list 2880.5625 820.26) 
(list 2954.585 820.81) 
(list 2954.585 820.987) 
(list 2880.5625 820.337)))
(apply 'command (append '("pline") coords '("c")))
(setq currobj (ssadd (entlast) currobj))
(setq coords (list 
(list 2880.5625 820.48) 
(list 2954.585 821.13) 
(list 2954.585 821.307) 
(list 2880.5625 820.557)))
(apply 'command (append '("pline") coords '("c")))
(setq currobj (ssadd (entlast) currobj))
(setq coords (list 
(list 2879.4375 820.557) 
(list 2805.415 821.307) 
(list 2805.415 821.13) 
(list 2879.4375 820.48)))
(apply 'command (append '("pline") coords '("c")))
(setq currobj (ssadd (entlast) currobj))
(setq coords (list 
(list 2879.4375 820.337) 
(list 2805.415 820.987) 
(list 2805.415 820.81) 
(list 2879.4375 820.26)))
(apply 'command (append '("pline") coords '("c")))
(setq currobj (ssadd (entlast) currobj))
(setq coords (list 
(list 2879.4375 820.117) 
(list 2805.415 820.667) 
(list 2805.415 820.49) 
(list 2879.4375 820.04)))
(apply 'command (append '("pline") coords '("c")))
(setq currobj (ssadd (entlast) currobj))
(setq coords (list 
(list 2879.4375 819.897) 
(list 2805.415 820.347) 
(list 2805.415 820.17) 
(list 2879.4375 819.82)))
(apply 'command (append '("pline") coords '("c")))
(setq currobj (ssadd (entlast) currobj))
(setq coords (list 
(list 2879.4375 819.677) 
(list 2805.415 820.027) 
(list 2805.415 819.85) 
(list 2879.4375 819.6)))
(apply 'command (append '("pline") coords '("c")))
(setq currobj (ssadd (entlast) currobj))
(setq coords (list 
(list 2879.4375 819.457) 
(list 2805.415 819.707) 
(list 2805.415 819.53) 
(list 2879.4375 819.38)))
(apply 'command (append '("pline") coords '("c")))
(setq currobj (ssadd (entlast) currobj))
(setq coords (list 
(list 2879.4375 819.237) 
(list 2805.415 819.387) 
(list 2805.415 819.21) 
(list 2879.4375 819.16)))
(apply 'command (append '("pline") coords '("c")))
(setq currobj (ssadd (entlast) currobj))
(setq coords (list 
(list 2879.4375 819.017) 
(list 2805.415 819.067) 
(list 2805.415 818.89) 
(list 2879.4375 818.94)))
(apply 'command (append '("pline") coords '("c")))
(setq currobj (ssadd (entlast) currobj))
(setq coords (list 
(list 2879.4375 818.797) 
(list 2805.415 818.747) 
(list 2805.415 818.57) 
(list 2879.4375 818.72)))
(apply 'command (append '("pline") coords '("c")))
(setq currobj (ssadd (entlast) currobj))
(setq coords (list 
(list 2879.4375 818.577) 
(list 2805.415 818.427) 
(list 2805.415 818.25) 
(list 2879.4375 818.5)))
(apply 'command (append '("pline") coords '("c")))
(setq currobj (ssadd (entlast) currobj))
(setq coords (list 
(list 2879.4375 818.357) 
(list 2805.415 818.107) 
(list 2805.415 817.93) 
(list 2879.4375 818.28)))
(apply 'command (append '("pline") coords '("c")))
(setq currobj (ssadd (entlast) currobj))
(setq coords (list 
(list 2879.4375 818.137) 
(list 2805.415 817.787) 
(list 2805.415 817.61) 
(list 2879.4375 818.06)))
(apply 'command (append '("pline") coords '("c")))
(setq currobj (ssadd (entlast) currobj))
(setq coords (list 
(list 2879.4375 817.917) 
(list 2805.415 817.467) 
(list 2805.415 817.29) 
(list 2879.4375 817.84)))
(apply 'command (append '("pline") coords '("c")))
(setq currobj (ssadd (entlast) currobj))
(setq coords (list 
(list 2879.4375 817.697) 
(list 2805.415 817.147) 
(list 2805.415 816.97) 
(list 2879.4375 817.62)))
(apply 'command (append '("pline") coords '("c")))
(setq currobj (ssadd (entlast) currobj))
(setq coords (list 
(list 2879.4375 817.477) 
(list 2805.415 816.827) 
(list 2805.415 816.65) 
(list 2879.4375 817.4)))
(apply 'command (append '("pline") coords '("c")))
(setq currobj (ssadd (entlast) currobj))
(command "_layer" "set" "nitride" "")
(command "_layer" "set" "text" "")
(command "_circle" "2879.0625,806.257" "0.075")
(command "_circle" "2879.0625,806.557" "0.075")
(command "_circle" "2879.0625,806.857" "0.075")
(command "_circle" "2879.0625,807.157" "0.075")
(command "_circle" "2879.0625,807.457" "0.075")
(command "_circle" "2878.7625,806.257" "0.075")
(command "_circle" "2878.7625,806.557" "0.075")
(command "_circle" "2878.7625,806.857" "0.075")
(command "_circle" "2878.7625,807.157" "0.075")
(command "_circle" "2878.7625,807.457" "0.075")
(command "_circle" "2878.4625,806.257" "0.075")
(command "_circle" "2878.4625,806.557" "0.075")
(command "_circle" "2878.4625,806.857" "0.075")
(command "_circle" "2878.4625,807.157" "0.075")
(command "_circle" "2878.4625,807.457" "0.075")
(command "_circle" "2878.1625,806.257" "0.075")
(command "_circle" "2878.1625,806.557" "0.075")
(command "_circle" "2878.1625,806.857" "0.075")
(command "_circle" "2878.1625,807.157" "0.075")
(command "_circle" "2878.1625,807.457" "0.075")
(command "_circle" "2877.8625,806.257" "0.075")
(command "_circle" "2877.8625,806.557" "0.075")
(command "_circle" "2877.8625,806.857" "0.075")
(command "_circle" "2877.8625,807.157" "0.075")
(command "_circle" "2877.8625,807.457" "0.075")
(command "_layer" "set" "nitride" "")
(setq coords (list 
(list 2880.2625 831.7) 
(list 2880.2625 836.7) 
(list 2879.7375 836.7) 
(list 2879.7375 831.7)))
(apply 'command (append '("pline") coords '("c")))
(setq currobj (ssadd (entlast) currobj))
(command "_layer" "set" "prebias" "")
(command "_rectangle" "2879.7375,831.7" "2880.2625,836.7")
(setq currobj (ssadd (entlast) currobj))
(command "_layer" "set" "nitride" "")
(setq cooledsinglenanobeam9 currobj)
(setq currobj nil)
(setq currobj (ssadd))
; DRAWING PHOTONIC CRYSTAL
(command "_layer" "set" "negYjunc" "")
(setq coords (list 
(list 2880.125 866.7) 
(list 2880 851.7) 
(list 2880 866.7)))
(apply 'command (append '("pline") coords '("c")))
(setq currobj (ssadd (entlast) currobj))
(setq coords (list 
(list 2880.2625 836.7) 
(list 2880.405 866.7) 
(list 2881.102 866.7) 
(list 2881.102 836.7)))
(apply 'command (append '("pline") coords '("c")))
(setq currobj (ssadd (entlast) currobj))
(setq coords (list 
(list 2879.875 866.7) 
(list 2880 851.7) 
(list 2880 866.7)))
(apply 'command (append '("pline") coords '("c")))
(setq currobj (ssadd (entlast) currobj))
(setq coords (list 
(list 2879.7375 836.7) 
(list 2879.595 866.7) 
(list 2878.898 866.7) 
(list 2878.898 836.7)))
(apply 'command (append '("pline") coords '("c")))
(setq currobj (ssadd (entlast) currobj))
(command "_layer" "set" "nitride" "")
(setq yjunction9 currobj)
(setq currobj nil)
(setq currobj (ssadd))
(setq tap9 nil)
(setq tap9 (ssadd))
(command "_layer" "set" "phc" "")
(setq coords (list 
(list 2880 866.7) 
(list 2880.125 866.7) 
(list 2880.125 866.7103) 
(list 2880.125 866.7206) 
(list 2880.125 866.7308) 
(list 2880.125 866.7411) 
(list 2880.125 866.7514) 
(list 2880.125 866.7617) 
(list 2880.125 866.7719) 
(list 2880.125 866.7822) 
(list 2880.125 866.7925) 
(list 2880.125 866.8028) 
(list 2880.125 866.8131) 
(list 2880.125 866.8233) 
(list 2880.125 866.8336) 
(list 2880.125 866.8439) 
(list 2880.125 866.8542) 
(list 2880.125 866.8644) 
(list 2880.125 866.8747) 
(list 2880.125 866.885) 
(list 2880.125 866.8953) 
(list 2880.125 866.9056) 
(list 2880.125 866.9158) 
(list 2880.125 866.9261) 
(list 2880.125 866.9364) 
(list 2880.125 866.9467) 
(list 2880.125 866.9569) 
(list 2880.125 866.9672) 
(list 2880.125 866.9775) 
(list 2880.125 866.9878) 
(list 2880.125 866.9981) 
(list 2880.125 867.0083) 
(list 2880.125 867.0186) 
(list 2880.125 867.0289) 
(list 2880.125 867.0392) 
(list 2880.125 867.0494) 
(list 2880.125 867.0597) 
(list 2880.125 867.07) 
(list 2880 867.07)))
(apply 'command (append '("pline") coords '("c")))
(setq tap9 (ssadd (entlast) tap9))
(command "_mirror" (entlast) "" "2880,900" "2880,901" "No")
(setq tap9 (ssadd (entlast) tap9))
(setq coords (list 
(list 2880.4147 866.7) 
(list 2880.405 866.7) 
(list 2880.4053 866.7103) 
(list 2880.4055 866.7206) 
(list 2880.4057 866.7308) 
(list 2880.4059 866.7411) 
(list 2880.4059 866.7514) 
(list 2880.4059 866.7617) 
(list 2880.4058 866.7719) 
(list 2880.4056 866.7822) 
(list 2880.4053 866.7925) 
(list 2880.4049 866.8028) 
(list 2880.4045 866.8131) 
(list 2880.404 866.8233) 
(list 2880.4035 866.8336) 
(list 2880.403 866.8439) 
(list 2880.4025 866.8542) 
(list 2880.402 866.8644) 
(list 2880.4017 866.8747) 
(list 2880.4014 866.885) 
(list 2880.4013 866.8953) 
(list 2880.4013 866.9056) 
(list 2880.4015 866.9158) 
(list 2880.4018 866.9261) 
(list 2880.4023 866.9364) 
(list 2880.403 866.9467) 
(list 2880.4039 866.9569) 
(list 2880.4049 866.9672) 
(list 2880.4059 866.9775) 
(list 2880.4071 866.9878) 
(list 2880.4084 866.9981) 
(list 2880.4096 867.0083) 
(list 2880.4108 867.0186) 
(list 2880.4119 867.0289) 
(list 2880.4129 867.0392) 
(list 2880.4137 867.0494) 
(list 2880.4143 867.0597) 
(list 2880.4147 867.07) 
(list 2880.4147 867.07)))
(apply 'command (append '("pline") coords '("c")))
(setq tap9 (ssadd (entlast) tap9))
(command "_mirror" (entlast) "" "2880,900" "2880,901" "No")
(setq tap9 (ssadd (entlast) tap9))
(setq coords (list 
(list 2881.102 866.7) 
(list 2880.4147 866.7) 
(list 2880.4147 866.7103) 
(list 2880.4147 866.7206) 
(list 2880.4147 866.7308) 
(list 2880.4147 866.7411) 
(list 2880.4147 866.7514) 
(list 2880.4147 866.7617) 
(list 2880.4147 866.7719) 
(list 2880.4147 866.7822) 
(list 2880.4147 866.7925) 
(list 2880.4147 866.8028) 
(list 2880.4147 866.8131) 
(list 2880.4147 866.8233) 
(list 2880.4147 866.8336) 
(list 2880.4147 866.8439) 
(list 2880.4147 866.8542) 
(list 2880.4147 866.8644) 
(list 2880.4147 866.8747) 
(list 2880.4147 866.885) 
(list 2880.4147 866.8953) 
(list 2880.4147 866.9056) 
(list 2880.4147 866.9158) 
(list 2880.4147 866.9261) 
(list 2880.4147 866.9364) 
(list 2880.4147 866.9467) 
(list 2880.4147 866.9569) 
(list 2880.4147 866.9672) 
(list 2880.4147 866.9775) 
(list 2880.4147 866.9878) 
(list 2880.4147 866.9981) 
(list 2880.4147 867.0083) 
(list 2880.4147 867.0186) 
(list 2880.4147 867.0289) 
(list 2880.4147 867.0392) 
(list 2880.4147 867.0494) 
(list 2880.4147 867.0597) 
(list 2880.4147 867.07) 
(list 2881.102 867.07)))
(apply 'command (append '("pline") coords '("c")))
(setq tap9 (ssadd (entlast) tap9))
(command "_mirror" (entlast) "" "2880,900" "2880,901" "No")
(setq tap9 (ssadd (entlast) tap9))
(setq coords (list 
(list 2880 867.07) 
(list 2880.125 867.07) 
(list 2880.125 867.0803) 
(list 2880.125 867.0906) 
(list 2880.125 867.1008) 
(list 2880.125 867.1111) 
(list 2880.125 867.1214) 
(list 2880.125 867.1317) 
(list 2880.125 867.1419) 
(list 2880.125 867.1522) 
(list 2880.125 867.1625) 
(list 2880.125 867.1728) 
(list 2880.125 867.1831) 
(list 2880.125 867.1933) 
(list 2880.125 867.2036) 
(list 2880.125 867.2139) 
(list 2880.125 867.2242) 
(list 2880.125 867.2344) 
(list 2880.125 867.2447) 
(list 2880.125 867.255) 
(list 2880.125 867.2653) 
(list 2880.125 867.2756) 
(list 2880.125 867.2858) 
(list 2880.125 867.2961) 
(list 2880.125 867.3064) 
(list 2880.125 867.3167) 
(list 2880.125 867.3269) 
(list 2880.125 867.3372) 
(list 2880.125 867.3475) 
(list 2880.125 867.3578) 
(list 2880.125 867.3681) 
(list 2880.125 867.3783) 
(list 2880.125 867.3886) 
(list 2880.125 867.3989) 
(list 2880.125 867.4092) 
(list 2880.125 867.4194) 
(list 2880.125 867.4297) 
(list 2880.125 867.44) 
(list 2880 867.44)))
(apply 'command (append '("pline") coords '("c")))
(setq tap9 (ssadd (entlast) tap9))
(command "_mirror" (entlast) "" "2880,900" "2880,901" "No")
(setq tap9 (ssadd (entlast) tap9))
(setq coords (list 
(list 2880.4245 867.07) 
(list 2880.4147 867.07) 
(list 2880.4149 867.0803) 
(list 2880.4147 867.0906) 
(list 2880.4143 867.1008) 
(list 2880.4136 867.1111) 
(list 2880.4126 867.1214) 
(list 2880.4114 867.1317) 
(list 2880.41 867.1419) 
(list 2880.4083 867.1522) 
(list 2880.4066 867.1625) 
(list 2880.4047 867.1728) 
(list 2880.4029 867.1831) 
(list 2880.401 867.1933) 
(list 2880.3993 867.2036) 
(list 2880.3978 867.2139) 
(list 2880.3964 867.2242) 
(list 2880.3953 867.2344) 
(list 2880.3946 867.2447) 
(list 2880.3942 867.255) 
(list 2880.3942 867.2653) 
(list 2880.3946 867.2756) 
(list 2880.3954 867.2858) 
(list 2880.3966 867.2961) 
(list 2880.3982 867.3064) 
(list 2880.4001 867.3167) 
(list 2880.4022 867.3269) 
(list 2880.4046 867.3372) 
(list 2880.4072 867.3475) 
(list 2880.4099 867.3578) 
(list 2880.4125 867.3681) 
(list 2880.4151 867.3783) 
(list 2880.4175 867.3886) 
(list 2880.4196 867.3989) 
(list 2880.4215 867.4092) 
(list 2880.4229 867.4194) 
(list 2880.4239 867.4297) 
(list 2880.4245 867.44) 
(list 2880.4245 867.44)))
(apply 'command (append '("pline") coords '("c")))
(setq tap9 (ssadd (entlast) tap9))
(command "_mirror" (entlast) "" "2880,900" "2880,901" "No")
(setq tap9 (ssadd (entlast) tap9))
(setq coords (list 
(list 2881.102 867.07) 
(list 2880.4245 867.07) 
(list 2880.4245 867.0803) 
(list 2880.4245 867.0906) 
(list 2880.4245 867.1008) 
(list 2880.4245 867.1111) 
(list 2880.4245 867.1214) 
(list 2880.4245 867.1317) 
(list 2880.4245 867.1419) 
(list 2880.4245 867.1522) 
(list 2880.4245 867.1625) 
(list 2880.4245 867.1728) 
(list 2880.4245 867.1831) 
(list 2880.4245 867.1933) 
(list 2880.4245 867.2036) 
(list 2880.4245 867.2139) 
(list 2880.4245 867.2242) 
(list 2880.4245 867.2344) 
(list 2880.4245 867.2447) 
(list 2880.4245 867.255) 
(list 2880.4245 867.2653) 
(list 2880.4245 867.2756) 
(list 2880.4245 867.2858) 
(list 2880.4245 867.2961) 
(list 2880.4245 867.3064) 
(list 2880.4245 867.3167) 
(list 2880.4245 867.3269) 
(list 2880.4245 867.3372) 
(list 2880.4245 867.3475) 
(list 2880.4245 867.3578) 
(list 2880.4245 867.3681) 
(list 2880.4245 867.3783) 
(list 2880.4245 867.3886) 
(list 2880.4245 867.3989) 
(list 2880.4245 867.4092) 
(list 2880.4245 867.4194) 
(list 2880.4245 867.4297) 
(list 2880.4245 867.44) 
(list 2881.102 867.44)))
(apply 'command (append '("pline") coords '("c")))
(setq tap9 (ssadd (entlast) tap9))
(command "_mirror" (entlast) "" "2880,900" "2880,901" "No")
(setq tap9 (ssadd (entlast) tap9))
(setq coords (list 
(list 2880 867.44) 
(list 2880.125 867.44) 
(list 2880.125 867.4503) 
(list 2880.125 867.4606) 
(list 2880.125 867.4708) 
(list 2880.125 867.4811) 
(list 2880.125 867.4914) 
(list 2880.125 867.5017) 
(list 2880.125 867.5119) 
(list 2880.125 867.5222) 
(list 2880.125 867.5325) 
(list 2880.125 867.5428) 
(list 2880.125 867.5531) 
(list 2880.125 867.5633) 
(list 2880.125 867.5736) 
(list 2880.125 867.5839) 
(list 2880.125 867.5942) 
(list 2880.125 867.6044) 
(list 2880.125 867.6147) 
(list 2880.125 867.625) 
(list 2880.125 867.6353) 
(list 2880.125 867.6456) 
(list 2880.125 867.6558) 
(list 2880.125 867.6661) 
(list 2880.125 867.6764) 
(list 2880.125 867.6867) 
(list 2880.125 867.6969) 
(list 2880.125 867.7072) 
(list 2880.125 867.7175) 
(list 2880.125 867.7278) 
(list 2880.125 867.7381) 
(list 2880.125 867.7483) 
(list 2880.125 867.7586) 
(list 2880.125 867.7689) 
(list 2880.125 867.7792) 
(list 2880.125 867.7894) 
(list 2880.125 867.7997) 
(list 2880.125 867.81) 
(list 2880 867.81)))
(apply 'command (append '("pline") coords '("c")))
(setq tap9 (ssadd (entlast) tap9))
(command "_mirror" (entlast) "" "2880,900" "2880,901" "No")
(setq tap9 (ssadd (entlast) tap9))
(setq coords (list 
(list 2880.4342 867.44) 
(list 2880.4245 867.44) 
(list 2880.4245 867.4503) 
(list 2880.424 867.4606) 
(list 2880.4229 867.4708) 
(list 2880.4214 867.4811) 
(list 2880.4194 867.4914) 
(list 2880.4169 867.5017) 
(list 2880.4141 867.5119) 
(list 2880.4111 867.5222) 
(list 2880.4079 867.5325) 
(list 2880.4045 867.5428) 
(list 2880.4012 867.5531) 
(list 2880.3981 867.5633) 
(list 2880.3951 867.5736) 
(list 2880.3925 867.5839) 
(list 2880.3903 867.5942) 
(list 2880.3886 867.6044) 
(list 2880.3875 867.6147) 
(list 2880.387 867.625) 
(list 2880.3871 867.6353) 
(list 2880.3879 867.6456) 
(list 2880.3893 867.6558) 
(list 2880.3914 867.6661) 
(list 2880.394 867.6764) 
(list 2880.3971 867.6867) 
(list 2880.4006 867.6969) 
(list 2880.4044 867.7072) 
(list 2880.4085 867.7175) 
(list 2880.4126 867.7278) 
(list 2880.4167 867.7381) 
(list 2880.4206 867.7483) 
(list 2880.4242 867.7586) 
(list 2880.4274 867.7689) 
(list 2880.4301 867.7792) 
(list 2880.4322 867.7894) 
(list 2880.4335 867.7997) 
(list 2880.4342 867.81) 
(list 2880.4342 867.81)))
(apply 'command (append '("pline") coords '("c")))
(setq tap9 (ssadd (entlast) tap9))
(command "_mirror" (entlast) "" "2880,900" "2880,901" "No")
(setq tap9 (ssadd (entlast) tap9))
(setq coords (list 
(list 2881.102 867.44) 
(list 2880.4342 867.44) 
(list 2880.4342 867.4503) 
(list 2880.4342 867.4606) 
(list 2880.4342 867.4708) 
(list 2880.4342 867.4811) 
(list 2880.4342 867.4914) 
(list 2880.4342 867.5017) 
(list 2880.4342 867.5119) 
(list 2880.4342 867.5222) 
(list 2880.4342 867.5325) 
(list 2880.4342 867.5428) 
(list 2880.4342 867.5531) 
(list 2880.4342 867.5633) 
(list 2880.4342 867.5736) 
(list 2880.4342 867.5839) 
(list 2880.4342 867.5942) 
(list 2880.4342 867.6044) 
(list 2880.4342 867.6147) 
(list 2880.4342 867.625) 
(list 2880.4342 867.6353) 
(list 2880.4342 867.6456) 
(list 2880.4342 867.6558) 
(list 2880.4342 867.6661) 
(list 2880.4342 867.6764) 
(list 2880.4342 867.6867) 
(list 2880.4342 867.6969) 
(list 2880.4342 867.7072) 
(list 2880.4342 867.7175) 
(list 2880.4342 867.7278) 
(list 2880.4342 867.7381) 
(list 2880.4342 867.7483) 
(list 2880.4342 867.7586) 
(list 2880.4342 867.7689) 
(list 2880.4342 867.7792) 
(list 2880.4342 867.7894) 
(list 2880.4342 867.7997) 
(list 2880.4342 867.81) 
(list 2881.102 867.81)))
(apply 'command (append '("pline") coords '("c")))
(setq tap9 (ssadd (entlast) tap9))
(command "_mirror" (entlast) "" "2880,900" "2880,901" "No")
(setq tap9 (ssadd (entlast) tap9))
(setq coords (list 
(list 2880 867.81) 
(list 2880.125 867.81) 
(list 2880.125 867.8203) 
(list 2880.125 867.8306) 
(list 2880.125 867.8408) 
(list 2880.125 867.8511) 
(list 2880.125 867.8614) 
(list 2880.125 867.8717) 
(list 2880.125 867.8819) 
(list 2880.125 867.8922) 
(list 2880.125 867.9025) 
(list 2880.125 867.9128) 
(list 2880.125 867.9231) 
(list 2880.125 867.9333) 
(list 2880.125 867.9436) 
(list 2880.125 867.9539) 
(list 2880.125 867.9642) 
(list 2880.125 867.9744) 
(list 2880.125 867.9847) 
(list 2880.125 867.995) 
(list 2880.125 868.0053) 
(list 2880.125 868.0156) 
(list 2880.125 868.0258) 
(list 2880.125 868.0361) 
(list 2880.125 868.0464) 
(list 2880.125 868.0567) 
(list 2880.125 868.0669) 
(list 2880.125 868.0772) 
(list 2880.125 868.0875) 
(list 2880.125 868.0978) 
(list 2880.125 868.1081) 
(list 2880.125 868.1183) 
(list 2880.125 868.1286) 
(list 2880.125 868.1389) 
(list 2880.125 868.1492) 
(list 2880.125 868.1594) 
(list 2880.125 868.1697) 
(list 2880.125 868.18) 
(list 2880 868.18)))
(apply 'command (append '("pline") coords '("c")))
(setq tap9 (ssadd (entlast) tap9))
(command "_mirror" (entlast) "" "2880,900" "2880,901" "No")
(setq tap9 (ssadd (entlast) tap9))
(setq coords (list 
(list 2880.4439 867.81) 
(list 2880.4342 867.81) 
(list 2880.4341 867.8203) 
(list 2880.4332 867.8306) 
(list 2880.4315 867.8408) 
(list 2880.4291 867.8511) 
(list 2880.4261 867.8614) 
(list 2880.4224 867.8717) 
(list 2880.4183 867.8819) 
(list 2880.4138 867.8922) 
(list 2880.4091 867.9025) 
(list 2880.4043 867.9128) 
(list 2880.3996 867.9231) 
(list 2880.3951 867.9333) 
(list 2880.391 867.9436) 
(list 2880.3873 867.9539) 
(list 2880.3843 867.9642) 
(list 2880.382 867.9744) 
(list 2880.3804 867.9847) 
(list 2880.3798 867.995) 
(list 2880.3801 868.0053) 
(list 2880.3812 868.0156) 
(list 2880.3833 868.0258) 
(list 2880.3862 868.0361) 
(list 2880.3898 868.0464) 
(list 2880.3941 868.0567) 
(list 2880.399 868.0669) 
(list 2880.4042 868.0772) 
(list 2880.4097 868.0875) 
(list 2880.4153 868.0978) 
(list 2880.4208 868.1081) 
(list 2880.4261 868.1183) 
(list 2880.4309 868.1286) 
(list 2880.4351 868.1389) 
(list 2880.4387 868.1492) 
(list 2880.4414 868.1594) 
(list 2880.4432 868.1697) 
(list 2880.4439 868.18) 
(list 2880.4439 868.18)))
(apply 'command (append '("pline") coords '("c")))
(setq tap9 (ssadd (entlast) tap9))
(command "_mirror" (entlast) "" "2880,900" "2880,901" "No")
(setq tap9 (ssadd (entlast) tap9))
(setq coords (list 
(list 2881.102 867.81) 
(list 2880.4439 867.81) 
(list 2880.4439 867.8203) 
(list 2880.4439 867.8306) 
(list 2880.4439 867.8408) 
(list 2880.4439 867.8511) 
(list 2880.4439 867.8614) 
(list 2880.4439 867.8717) 
(list 2880.4439 867.8819) 
(list 2880.4439 867.8922) 
(list 2880.4439 867.9025) 
(list 2880.4439 867.9128) 
(list 2880.4439 867.9231) 
(list 2880.4439 867.9333) 
(list 2880.4439 867.9436) 
(list 2880.4439 867.9539) 
(list 2880.4439 867.9642) 
(list 2880.4439 867.9744) 
(list 2880.4439 867.9847) 
(list 2880.4439 867.995) 
(list 2880.4439 868.0053) 
(list 2880.4439 868.0156) 
(list 2880.4439 868.0258) 
(list 2880.4439 868.0361) 
(list 2880.4439 868.0464) 
(list 2880.4439 868.0567) 
(list 2880.4439 868.0669) 
(list 2880.4439 868.0772) 
(list 2880.4439 868.0875) 
(list 2880.4439 868.0978) 
(list 2880.4439 868.1081) 
(list 2880.4439 868.1183) 
(list 2880.4439 868.1286) 
(list 2880.4439 868.1389) 
(list 2880.4439 868.1492) 
(list 2880.4439 868.1594) 
(list 2880.4439 868.1697) 
(list 2880.4439 868.18) 
(list 2881.102 868.18)))
(apply 'command (append '("pline") coords '("c")))
(setq tap9 (ssadd (entlast) tap9))
(command "_mirror" (entlast) "" "2880,900" "2880,901" "No")
(setq tap9 (ssadd (entlast) tap9))
(setq coords (list 
(list 2880 868.18) 
(list 2880.125 868.18) 
(list 2880.125 868.1903) 
(list 2880.125 868.2006) 
(list 2880.125 868.2108) 
(list 2880.125 868.2211) 
(list 2880.125 868.2314) 
(list 2880.125 868.2417) 
(list 2880.125 868.2519) 
(list 2880.125 868.2622) 
(list 2880.125 868.2725) 
(list 2880.125 868.2828) 
(list 2880.125 868.2931) 
(list 2880.125 868.3033) 
(list 2880.125 868.3136) 
(list 2880.125 868.3239) 
(list 2880.125 868.3342) 
(list 2880.125 868.3444) 
(list 2880.125 868.3547) 
(list 2880.125 868.365) 
(list 2880.125 868.3753) 
(list 2880.125 868.3856) 
(list 2880.125 868.3958) 
(list 2880.125 868.4061) 
(list 2880.125 868.4164) 
(list 2880.125 868.4267) 
(list 2880.125 868.4369) 
(list 2880.125 868.4472) 
(list 2880.125 868.4575) 
(list 2880.125 868.4678) 
(list 2880.125 868.4781) 
(list 2880.125 868.4883) 
(list 2880.125 868.4986) 
(list 2880.125 868.5089) 
(list 2880.125 868.5192) 
(list 2880.125 868.5294) 
(list 2880.125 868.5397) 
(list 2880.125 868.55) 
(list 2880 868.55)))
(apply 'command (append '("pline") coords '("c")))
(setq tap9 (ssadd (entlast) tap9))
(command "_mirror" (entlast) "" "2880,900" "2880,901" "No")
(setq tap9 (ssadd (entlast) tap9))
(setq coords (list 
(list 2880.4537 868.18) 
(list 2880.4439 868.18) 
(list 2880.4437 868.1903) 
(list 2880.4424 868.2006) 
(list 2880.4401 868.2108) 
(list 2880.4369 868.2211) 
(list 2880.4328 868.2314) 
(list 2880.4279 868.2417) 
(list 2880.4225 868.2519) 
(list 2880.4166 868.2622) 
(list 2880.4104 868.2725) 
(list 2880.4041 868.2828) 
(list 2880.398 868.2931) 
(list 2880.3921 868.3033) 
(list 2880.3868 868.3136) 
(list 2880.3821 868.3239) 
(list 2880.3782 868.3342) 
(list 2880.3753 868.3444) 
(list 2880.3734 868.3547) 
(list 2880.3726 868.365) 
(list 2880.373 868.3753) 
(list 2880.3745 868.3856) 
(list 2880.3772 868.3958) 
(list 2880.3809 868.4061) 
(list 2880.3856 868.4164) 
(list 2880.3912 868.4267) 
(list 2880.3974 868.4369) 
(list 2880.404 868.4472) 
(list 2880.411 868.4575) 
(list 2880.4181 868.4678) 
(list 2880.425 868.4781) 
(list 2880.4316 868.4883) 
(list 2880.4376 868.4986) 
(list 2880.4429 868.5089) 
(list 2880.4473 868.5192) 
(list 2880.4506 868.5294) 
(list 2880.4528 868.5397) 
(list 2880.4537 868.55) 
(list 2880.4537 868.55)))
(apply 'command (append '("pline") coords '("c")))
(setq tap9 (ssadd (entlast) tap9))
(command "_mirror" (entlast) "" "2880,900" "2880,901" "No")
(setq tap9 (ssadd (entlast) tap9))
(setq coords (list 
(list 2881.102 868.18) 
(list 2880.4537 868.18) 
(list 2880.4537 868.1903) 
(list 2880.4537 868.2006) 
(list 2880.4537 868.2108) 
(list 2880.4537 868.2211) 
(list 2880.4537 868.2314) 
(list 2880.4537 868.2417) 
(list 2880.4537 868.2519) 
(list 2880.4537 868.2622) 
(list 2880.4537 868.2725) 
(list 2880.4537 868.2828) 
(list 2880.4537 868.2931) 
(list 2880.4537 868.3033) 
(list 2880.4537 868.3136) 
(list 2880.4537 868.3239) 
(list 2880.4537 868.3342) 
(list 2880.4537 868.3444) 
(list 2880.4537 868.3547) 
(list 2880.4537 868.365) 
(list 2880.4537 868.3753) 
(list 2880.4537 868.3856) 
(list 2880.4537 868.3958) 
(list 2880.4537 868.4061) 
(list 2880.4537 868.4164) 
(list 2880.4537 868.4267) 
(list 2880.4537 868.4369) 
(list 2880.4537 868.4472) 
(list 2880.4537 868.4575) 
(list 2880.4537 868.4678) 
(list 2880.4537 868.4781) 
(list 2880.4537 868.4883) 
(list 2880.4537 868.4986) 
(list 2880.4537 868.5089) 
(list 2880.4537 868.5192) 
(list 2880.4537 868.5294) 
(list 2880.4537 868.5397) 
(list 2880.4537 868.55) 
(list 2881.102 868.55)))
(apply 'command (append '("pline") coords '("c")))
(setq tap9 (ssadd (entlast) tap9))
(command "_mirror" (entlast) "" "2880,900" "2880,901" "No")
(setq tap9 (ssadd (entlast) tap9))
(setq coords (list 
(list 2880 868.55) 
(list 2880.125 868.55) 
(list 2880.125 868.5603) 
(list 2880.125 868.5706) 
(list 2880.125 868.5808) 
(list 2880.125 868.5911) 
(list 2880.125 868.6014) 
(list 2880.125 868.6117) 
(list 2880.125 868.6219) 
(list 2880.125 868.6322) 
(list 2880.125 868.6425) 
(list 2880.125 868.6528) 
(list 2880.125 868.6631) 
(list 2880.125 868.6733) 
(list 2880.125 868.6836) 
(list 2880.125 868.6939) 
(list 2880.125 868.7042) 
(list 2880.125 868.7144) 
(list 2880.125 868.7247) 
(list 2880.125 868.735) 
(list 2880.125 868.7453) 
(list 2880.125 868.7556) 
(list 2880.125 868.7658) 
(list 2880.125 868.7761) 
(list 2880.125 868.7864) 
(list 2880.125 868.7967) 
(list 2880.125 868.8069) 
(list 2880.125 868.8172) 
(list 2880.125 868.8275) 
(list 2880.125 868.8378) 
(list 2880.125 868.8481) 
(list 2880.125 868.8583) 
(list 2880.125 868.8686) 
(list 2880.125 868.8789) 
(list 2880.125 868.8892) 
(list 2880.125 868.8994) 
(list 2880.125 868.9097) 
(list 2880.125 868.92) 
(list 2880 868.92)))
(apply 'command (append '("pline") coords '("c")))
(setq tap9 (ssadd (entlast) tap9))
(command "_mirror" (entlast) "" "2880,900" "2880,901" "No")
(setq tap9 (ssadd (entlast) tap9))
(setq coords (list 
(list 2880.4634 868.55) 
(list 2880.4537 868.55) 
(list 2880.4533 868.5603) 
(list 2880.4516 868.5706) 
(list 2880.4487 868.5808) 
(list 2880.4446 868.5911) 
(list 2880.4395 868.6014) 
(list 2880.4334 868.6117) 
(list 2880.4266 868.6219) 
(list 2880.4193 868.6322) 
(list 2880.4117 868.6425) 
(list 2880.4039 868.6528) 
(list 2880.3964 868.6631) 
(list 2880.3892 868.6733) 
(list 2880.3826 868.6836) 
(list 2880.3769 868.6939) 
(list 2880.3721 868.7042) 
(list 2880.3686 868.7144) 
(list 2880.3663 868.7247) 
(list 2880.3654 868.735) 
(list 2880.3659 868.7453) 
(list 2880.3678 868.7556) 
(list 2880.3711 868.7658) 
(list 2880.3757 868.7761) 
(list 2880.3815 868.7864) 
(list 2880.3882 868.7967) 
(list 2880.3957 868.8069) 
(list 2880.4038 868.8172) 
(list 2880.4123 868.8275) 
(list 2880.4208 868.8378) 
(list 2880.4292 868.8481) 
(list 2880.4371 868.8583) 
(list 2880.4443 868.8686) 
(list 2880.4507 868.8789) 
(list 2880.4559 868.8892) 
(list 2880.4598 868.8994) 
(list 2880.4624 868.9097) 
(list 2880.4634 868.92) 
(list 2880.4634 868.92)))
(apply 'command (append '("pline") coords '("c")))
(setq tap9 (ssadd (entlast) tap9))
(command "_mirror" (entlast) "" "2880,900" "2880,901" "No")
(setq tap9 (ssadd (entlast) tap9))
(setq coords (list 
(list 2881.102 868.55) 
(list 2880.4634 868.55) 
(list 2880.4634 868.5603) 
(list 2880.4634 868.5706) 
(list 2880.4634 868.5808) 
(list 2880.4634 868.5911) 
(list 2880.4634 868.6014) 
(list 2880.4634 868.6117) 
(list 2880.4634 868.6219) 
(list 2880.4634 868.6322) 
(list 2880.4634 868.6425) 
(list 2880.4634 868.6528) 
(list 2880.4634 868.6631) 
(list 2880.4634 868.6733) 
(list 2880.4634 868.6836) 
(list 2880.4634 868.6939) 
(list 2880.4634 868.7042) 
(list 2880.4634 868.7144) 
(list 2880.4634 868.7247) 
(list 2880.4634 868.735) 
(list 2880.4634 868.7453) 
(list 2880.4634 868.7556) 
(list 2880.4634 868.7658) 
(list 2880.4634 868.7761) 
(list 2880.4634 868.7864) 
(list 2880.4634 868.7967) 
(list 2880.4634 868.8069) 
(list 2880.4634 868.8172) 
(list 2880.4634 868.8275) 
(list 2880.4634 868.8378) 
(list 2880.4634 868.8481) 
(list 2880.4634 868.8583) 
(list 2880.4634 868.8686) 
(list 2880.4634 868.8789) 
(list 2880.4634 868.8892) 
(list 2880.4634 868.8994) 
(list 2880.4634 868.9097) 
(list 2880.4634 868.92) 
(list 2881.102 868.92)))
(apply 'command (append '("pline") coords '("c")))
(setq tap9 (ssadd (entlast) tap9))
(command "_mirror" (entlast) "" "2880,900" "2880,901" "No")
(setq tap9 (ssadd (entlast) tap9))
(setq coords (list 
(list 2880 868.92) 
(list 2880.125 868.92) 
(list 2880.125 868.9303) 
(list 2880.125 868.9406) 
(list 2880.125 868.9508) 
(list 2880.125 868.9611) 
(list 2880.125 868.9714) 
(list 2880.125 868.9817) 
(list 2880.125 868.9919) 
(list 2880.125 869.0022) 
(list 2880.125 869.0125) 
(list 2880.125 869.0228) 
(list 2880.125 869.0331) 
(list 2880.125 869.0433) 
(list 2880.125 869.0536) 
(list 2880.125 869.0639) 
(list 2880.125 869.0742) 
(list 2880.125 869.0844) 
(list 2880.125 869.0947) 
(list 2880.125 869.105) 
(list 2880.125 869.1153) 
(list 2880.125 869.1256) 
(list 2880.125 869.1358) 
(list 2880.125 869.1461) 
(list 2880.125 869.1564) 
(list 2880.125 869.1667) 
(list 2880.125 869.1769) 
(list 2880.125 869.1872) 
(list 2880.125 869.1975) 
(list 2880.125 869.2078) 
(list 2880.125 869.2181) 
(list 2880.125 869.2283) 
(list 2880.125 869.2386) 
(list 2880.125 869.2489) 
(list 2880.125 869.2592) 
(list 2880.125 869.2694) 
(list 2880.125 869.2797) 
(list 2880.125 869.29) 
(list 2880 869.29)))
(apply 'command (append '("pline") coords '("c")))
(setq tap9 (ssadd (entlast) tap9))
(command "_mirror" (entlast) "" "2880,900" "2880,901" "No")
(setq tap9 (ssadd (entlast) tap9))
(setq coords (list 
(list 2880.4731 868.92) 
(list 2880.4634 868.92) 
(list 2880.4629 868.9303) 
(list 2880.4608 868.9406) 
(list 2880.4573 868.9508) 
(list 2880.4524 868.9611) 
(list 2880.4462 868.9714) 
(list 2880.4389 868.9817) 
(list 2880.4308 868.9919) 
(list 2880.422 869.0022) 
(list 2880.4129 869.0125) 
(list 2880.4037 869.0228) 
(list 2880.3947 869.0331) 
(list 2880.3862 869.0433) 
(list 2880.3784 869.0536) 
(list 2880.3717 869.0639) 
(list 2880.3661 869.0742) 
(list 2880.3619 869.0844) 
(list 2880.3592 869.0947) 
(list 2880.3582 869.105) 
(list 2880.3588 869.1153) 
(list 2880.3611 869.1256) 
(list 2880.3651 869.1358) 
(list 2880.3705 869.1461) 
(list 2880.3773 869.1564) 
(list 2880.3852 869.1667) 
(list 2880.3941 869.1769) 
(list 2880.4036 869.1872) 
(list 2880.4136 869.1975) 
(list 2880.4235 869.2078) 
(list 2880.4333 869.2181) 
(list 2880.4426 869.2283) 
(list 2880.451 869.2386) 
(list 2880.4584 869.2489) 
(list 2880.4645 869.2592) 
(list 2880.469 869.2694) 
(list 2880.472 869.2797) 
(list 2880.4731 869.29) 
(list 2880.4731 869.29)))
(apply 'command (append '("pline") coords '("c")))
(setq tap9 (ssadd (entlast) tap9))
(command "_mirror" (entlast) "" "2880,900" "2880,901" "No")
(setq tap9 (ssadd (entlast) tap9))
(setq coords (list 
(list 2881.102 868.92) 
(list 2880.4731 868.92) 
(list 2880.4731 868.9303) 
(list 2880.4731 868.9406) 
(list 2880.4731 868.9508) 
(list 2880.4731 868.9611) 
(list 2880.4731 868.9714) 
(list 2880.4731 868.9817) 
(list 2880.4731 868.9919) 
(list 2880.4731 869.0022) 
(list 2880.4731 869.0125) 
(list 2880.4731 869.0228) 
(list 2880.4731 869.0331) 
(list 2880.4731 869.0433) 
(list 2880.4731 869.0536) 
(list 2880.4731 869.0639) 
(list 2880.4731 869.0742) 
(list 2880.4731 869.0844) 
(list 2880.4731 869.0947) 
(list 2880.4731 869.105) 
(list 2880.4731 869.1153) 
(list 2880.4731 869.1256) 
(list 2880.4731 869.1358) 
(list 2880.4731 869.1461) 
(list 2880.4731 869.1564) 
(list 2880.4731 869.1667) 
(list 2880.4731 869.1769) 
(list 2880.4731 869.1872) 
(list 2880.4731 869.1975) 
(list 2880.4731 869.2078) 
(list 2880.4731 869.2181) 
(list 2880.4731 869.2283) 
(list 2880.4731 869.2386) 
(list 2880.4731 869.2489) 
(list 2880.4731 869.2592) 
(list 2880.4731 869.2694) 
(list 2880.4731 869.2797) 
(list 2880.4731 869.29) 
(list 2881.102 869.29)))
(apply 'command (append '("pline") coords '("c")))
(setq tap9 (ssadd (entlast) tap9))
(command "_mirror" (entlast) "" "2880,900" "2880,901" "No")
(setq tap9 (ssadd (entlast) tap9))
(setq coords (list 
(list 2880 869.29) 
(list 2880.125 869.29) 
(list 2880.125 869.3003) 
(list 2880.125 869.3106) 
(list 2880.125 869.3208) 
(list 2880.125 869.3311) 
(list 2880.125 869.3414) 
(list 2880.125 869.3517) 
(list 2880.125 869.3619) 
(list 2880.125 869.3722) 
(list 2880.125 869.3825) 
(list 2880.125 869.3928) 
(list 2880.125 869.4031) 
(list 2880.125 869.4133) 
(list 2880.125 869.4236) 
(list 2880.125 869.4339) 
(list 2880.125 869.4442) 
(list 2880.125 869.4544) 
(list 2880.125 869.4647) 
(list 2880.125 869.475) 
(list 2880.125 869.4853) 
(list 2880.125 869.4956) 
(list 2880.125 869.5058) 
(list 2880.125 869.5161) 
(list 2880.125 869.5264) 
(list 2880.125 869.5367) 
(list 2880.125 869.5469) 
(list 2880.125 869.5572) 
(list 2880.125 869.5675) 
(list 2880.125 869.5778) 
(list 2880.125 869.5881) 
(list 2880.125 869.5983) 
(list 2880.125 869.6086) 
(list 2880.125 869.6189) 
(list 2880.125 869.6292) 
(list 2880.125 869.6394) 
(list 2880.125 869.6497) 
(list 2880.125 869.66) 
(list 2880 869.66)))
(apply 'command (append '("pline") coords '("c")))
(setq tap9 (ssadd (entlast) tap9))
(command "_mirror" (entlast) "" "2880,900" "2880,901" "No")
(setq tap9 (ssadd (entlast) tap9))
(setq coords (list 
(list 2880.4829 869.29) 
(list 2880.4731 869.29) 
(list 2880.4725 869.3003) 
(list 2880.4701 869.3106) 
(list 2880.4659 869.3208) 
(list 2880.4601 869.3311) 
(list 2880.4529 869.3414) 
(list 2880.4444 869.3517) 
(list 2880.4349 869.3619) 
(list 2880.4248 869.3722) 
(list 2880.4142 869.3825) 
(list 2880.4035 869.3928) 
(list 2880.3931 869.4031) 
(list 2880.3832 869.4133) 
(list 2880.3743 869.4236) 
(list 2880.3664 869.4339) 
(list 2880.36 869.4442) 
(list 2880.3552 869.4544) 
(list 2880.3522 869.4647) 
(list 2880.351 869.475) 
(list 2880.3518 869.4853) 
(list 2880.3545 869.4956) 
(list 2880.359 869.5058) 
(list 2880.3653 869.5161) 
(list 2880.3731 869.5264) 
(list 2880.3823 869.5367) 
(list 2880.3925 869.5469) 
(list 2880.4034 869.5572) 
(list 2880.4148 869.5675) 
(list 2880.4263 869.5778) 
(list 2880.4375 869.5881) 
(list 2880.4481 869.5983) 
(list 2880.4577 869.6086) 
(list 2880.4662 869.6189) 
(list 2880.4731 869.6292) 
(list 2880.4783 869.6394) 
(list 2880.4816 869.6497) 
(list 2880.4829 869.66) 
(list 2880.4829 869.66)))
(apply 'command (append '("pline") coords '("c")))
(setq tap9 (ssadd (entlast) tap9))
(command "_mirror" (entlast) "" "2880,900" "2880,901" "No")
(setq tap9 (ssadd (entlast) tap9))
(setq coords (list 
(list 2881.102 869.29) 
(list 2880.4829 869.29) 
(list 2880.4829 869.3003) 
(list 2880.4829 869.3106) 
(list 2880.4829 869.3208) 
(list 2880.4829 869.3311) 
(list 2880.4829 869.3414) 
(list 2880.4829 869.3517) 
(list 2880.4829 869.3619) 
(list 2880.4829 869.3722) 
(list 2880.4829 869.3825) 
(list 2880.4829 869.3928) 
(list 2880.4829 869.4031) 
(list 2880.4829 869.4133) 
(list 2880.4829 869.4236) 
(list 2880.4829 869.4339) 
(list 2880.4829 869.4442) 
(list 2880.4829 869.4544) 
(list 2880.4829 869.4647) 
(list 2880.4829 869.475) 
(list 2880.4829 869.4853) 
(list 2880.4829 869.4956) 
(list 2880.4829 869.5058) 
(list 2880.4829 869.5161) 
(list 2880.4829 869.5264) 
(list 2880.4829 869.5367) 
(list 2880.4829 869.5469) 
(list 2880.4829 869.5572) 
(list 2880.4829 869.5675) 
(list 2880.4829 869.5778) 
(list 2880.4829 869.5881) 
(list 2880.4829 869.5983) 
(list 2880.4829 869.6086) 
(list 2880.4829 869.6189) 
(list 2880.4829 869.6292) 
(list 2880.4829 869.6394) 
(list 2880.4829 869.6497) 
(list 2880.4829 869.66) 
(list 2881.102 869.66)))
(apply 'command (append '("pline") coords '("c")))
(setq tap9 (ssadd (entlast) tap9))
(command "_mirror" (entlast) "" "2880,900" "2880,901" "No")
(setq tap9 (ssadd (entlast) tap9))
(setq coords (list 
(list 2880 869.66) 
(list 2880.125 869.66) 
(list 2880.125 869.6703) 
(list 2880.125 869.6806) 
(list 2880.125 869.6908) 
(list 2880.125 869.7011) 
(list 2880.125 869.7114) 
(list 2880.125 869.7217) 
(list 2880.125 869.7319) 
(list 2880.125 869.7422) 
(list 2880.125 869.7525) 
(list 2880.125 869.7628) 
(list 2880.125 869.7731) 
(list 2880.125 869.7833) 
(list 2880.125 869.7936) 
(list 2880.125 869.8039) 
(list 2880.125 869.8142) 
(list 2880.125 869.8244) 
(list 2880.125 869.8347) 
(list 2880.125 869.845) 
(list 2880.125 869.8553) 
(list 2880.125 869.8656) 
(list 2880.125 869.8758) 
(list 2880.125 869.8861) 
(list 2880.125 869.8964) 
(list 2880.125 869.9067) 
(list 2880.125 869.9169) 
(list 2880.125 869.9272) 
(list 2880.125 869.9375) 
(list 2880.125 869.9478) 
(list 2880.125 869.9581) 
(list 2880.125 869.9683) 
(list 2880.125 869.9786) 
(list 2880.125 869.9889) 
(list 2880.125 869.9992) 
(list 2880.125 870.0094) 
(list 2880.125 870.0197) 
(list 2880.125 870.03) 
(list 2880 870.03)))
(apply 'command (append '("pline") coords '("c")))
(setq tap9 (ssadd (entlast) tap9))
(command "_mirror" (entlast) "" "2880,900" "2880,901" "No")
(setq tap9 (ssadd (entlast) tap9))
(setq coords (list 
(list 2880.4926 869.66) 
(list 2880.4829 869.66) 
(list 2880.4821 869.6703) 
(list 2880.4793 869.6806) 
(list 2880.4745 869.6908) 
(list 2880.4679 869.7011) 
(list 2880.4596 869.7114) 
(list 2880.4499 869.7217) 
(list 2880.4391 869.7319) 
(list 2880.4275 869.7422) 
(list 2880.4154 869.7525) 
(list 2880.4033 869.7628) 
(list 2880.3915 869.7731) 
(list 2880.3803 869.7833) 
(list 2880.3701 869.7936) 
(list 2880.3612 869.8039) 
(list 2880.3539 869.8142) 
(list 2880.3485 869.8244) 
(list 2880.3451 869.8347) 
(list 2880.3438 869.845) 
(list 2880.3447 869.8553) 
(list 2880.3478 869.8656) 
(list 2880.3529 869.8758) 
(list 2880.3601 869.8861) 
(list 2880.3689 869.8964) 
(list 2880.3793 869.9067) 
(list 2880.3908 869.9169) 
(list 2880.4032 869.9272) 
(list 2880.4161 869.9375) 
(list 2880.429 869.9478) 
(list 2880.4417 869.9581) 
(list 2880.4536 869.9683) 
(list 2880.4644 869.9786) 
(list 2880.4739 869.9889) 
(list 2880.4817 869.9992) 
(list 2880.4875 870.0094) 
(list 2880.4912 870.0197) 
(list 2880.4926 870.03) 
(list 2880.4926 870.03)))
(apply 'command (append '("pline") coords '("c")))
(setq tap9 (ssadd (entlast) tap9))
(command "_mirror" (entlast) "" "2880,900" "2880,901" "No")
(setq tap9 (ssadd (entlast) tap9))
(setq coords (list 
(list 2881.102 869.66) 
(list 2880.4926 869.66) 
(list 2880.4926 869.6703) 
(list 2880.4926 869.6806) 
(list 2880.4926 869.6908) 
(list 2880.4926 869.7011) 
(list 2880.4926 869.7114) 
(list 2880.4926 869.7217) 
(list 2880.4926 869.7319) 
(list 2880.4926 869.7422) 
(list 2880.4926 869.7525) 
(list 2880.4926 869.7628) 
(list 2880.4926 869.7731) 
(list 2880.4926 869.7833) 
(list 2880.4926 869.7936) 
(list 2880.4926 869.8039) 
(list 2880.4926 869.8142) 
(list 2880.4926 869.8244) 
(list 2880.4926 869.8347) 
(list 2880.4926 869.845) 
(list 2880.4926 869.8553) 
(list 2880.4926 869.8656) 
(list 2880.4926 869.8758) 
(list 2880.4926 869.8861) 
(list 2880.4926 869.8964) 
(list 2880.4926 869.9067) 
(list 2880.4926 869.9169) 
(list 2880.4926 869.9272) 
(list 2880.4926 869.9375) 
(list 2880.4926 869.9478) 
(list 2880.4926 869.9581) 
(list 2880.4926 869.9683) 
(list 2880.4926 869.9786) 
(list 2880.4926 869.9889) 
(list 2880.4926 869.9992) 
(list 2880.4926 870.0094) 
(list 2880.4926 870.0197) 
(list 2880.4926 870.03) 
(list 2881.102 870.03)))
(apply 'command (append '("pline") coords '("c")))
(setq tap9 (ssadd (entlast) tap9))
(command "_mirror" (entlast) "" "2880,900" "2880,901" "No")
(setq tap9 (ssadd (entlast) tap9))
(setq coords (list 
(list 2880 870.03) 
(list 2880.125 870.03) 
(list 2880.125 870.0403) 
(list 2880.125 870.0506) 
(list 2880.125 870.0608) 
(list 2880.125 870.0711) 
(list 2880.125 870.0814) 
(list 2880.125 870.0917) 
(list 2880.125 870.1019) 
(list 2880.125 870.1122) 
(list 2880.125 870.1225) 
(list 2880.125 870.1328) 
(list 2880.125 870.1431) 
(list 2880.125 870.1533) 
(list 2880.125 870.1636) 
(list 2880.125 870.1739) 
(list 2880.125 870.1842) 
(list 2880.125 870.1944) 
(list 2880.125 870.2047) 
(list 2880.125 870.215) 
(list 2880.125 870.2253) 
(list 2880.125 870.2356) 
(list 2880.125 870.2458) 
(list 2880.125 870.2561) 
(list 2880.125 870.2664) 
(list 2880.125 870.2767) 
(list 2880.125 870.2869) 
(list 2880.125 870.2972) 
(list 2880.125 870.3075) 
(list 2880.125 870.3178) 
(list 2880.125 870.3281) 
(list 2880.125 870.3383) 
(list 2880.125 870.3486) 
(list 2880.125 870.3589) 
(list 2880.125 870.3692) 
(list 2880.125 870.3794) 
(list 2880.125 870.3897) 
(list 2880.125 870.4) 
(list 2880 870.4)))
(apply 'command (append '("pline") coords '("c")))
(setq tap9 (ssadd (entlast) tap9))
(command "_mirror" (entlast) "" "2880,900" "2880,901" "No")
(setq tap9 (ssadd (entlast) tap9))
(setq coords (list 
(list 2880.5023 870.03) 
(list 2880.4926 870.03) 
(list 2880.4917 870.0403) 
(list 2880.4885 870.0506) 
(list 2880.4831 870.0608) 
(list 2880.4756 870.0711) 
(list 2880.4663 870.0814) 
(list 2880.4554 870.0917) 
(list 2880.4433 870.1019) 
(list 2880.4302 870.1122) 
(list 2880.4167 870.1225) 
(list 2880.4031 870.1328) 
(list 2880.3898 870.1431) 
(list 2880.3773 870.1533) 
(list 2880.3659 870.1636) 
(list 2880.356 870.1739) 
(list 2880.3479 870.1842) 
(list 2880.3418 870.1944) 
(list 2880.338 870.2047) 
(list 2880.3366 870.215) 
(list 2880.3376 870.2253) 
(list 2880.3411 870.2356) 
(list 2880.3469 870.2458) 
(list 2880.3548 870.2561) 
(list 2880.3648 870.2664) 
(list 2880.3763 870.2767) 
(list 2880.3892 870.2869) 
(list 2880.403 870.2972) 
(list 2880.4174 870.3075) 
(list 2880.4318 870.3178) 
(list 2880.4458 870.3281) 
(list 2880.4591 870.3383) 
(list 2880.4712 870.3486) 
(list 2880.4817 870.3589) 
(list 2880.4903 870.3692) 
(list 2880.4967 870.3794) 
(list 2880.5008 870.3897) 
(list 2880.5023 870.4) 
(list 2880.5023 870.4)))
(apply 'command (append '("pline") coords '("c")))
(setq tap9 (ssadd (entlast) tap9))
(command "_mirror" (entlast) "" "2880,900" "2880,901" "No")
(setq tap9 (ssadd (entlast) tap9))
(setq coords (list 
(list 2881.102 870.03) 
(list 2880.5023 870.03) 
(list 2880.5023 870.0403) 
(list 2880.5023 870.0506) 
(list 2880.5023 870.0608) 
(list 2880.5023 870.0711) 
(list 2880.5023 870.0814) 
(list 2880.5023 870.0917) 
(list 2880.5023 870.1019) 
(list 2880.5023 870.1122) 
(list 2880.5023 870.1225) 
(list 2880.5023 870.1328) 
(list 2880.5023 870.1431) 
(list 2880.5023 870.1533) 
(list 2880.5023 870.1636) 
(list 2880.5023 870.1739) 
(list 2880.5023 870.1842) 
(list 2880.5023 870.1944) 
(list 2880.5023 870.2047) 
(list 2880.5023 870.215) 
(list 2880.5023 870.2253) 
(list 2880.5023 870.2356) 
(list 2880.5023 870.2458) 
(list 2880.5023 870.2561) 
(list 2880.5023 870.2664) 
(list 2880.5023 870.2767) 
(list 2880.5023 870.2869) 
(list 2880.5023 870.2972) 
(list 2880.5023 870.3075) 
(list 2880.5023 870.3178) 
(list 2880.5023 870.3281) 
(list 2880.5023 870.3383) 
(list 2880.5023 870.3486) 
(list 2880.5023 870.3589) 
(list 2880.5023 870.3692) 
(list 2880.5023 870.3794) 
(list 2880.5023 870.3897) 
(list 2880.5023 870.4) 
(list 2881.102 870.4)))
(apply 'command (append '("pline") coords '("c")))
(setq tap9 (ssadd (entlast) tap9))
(command "_mirror" (entlast) "" "2880,900" "2880,901" "No")
(setq tap9 (ssadd (entlast) tap9))
(setq coords (list 
(list 2880 870.4) 
(list 2880.125 870.4) 
(list 2880.125 870.4103) 
(list 2880.125 870.4206) 
(list 2880.125 870.4308) 
(list 2880.125 870.4411) 
(list 2880.125 870.4514) 
(list 2880.125 870.4617) 
(list 2880.125 870.4719) 
(list 2880.125 870.4822) 
(list 2880.125 870.4925) 
(list 2880.125 870.5028) 
(list 2880.125 870.5131) 
(list 2880.125 870.5233) 
(list 2880.125 870.5336) 
(list 2880.125 870.5439) 
(list 2880.125 870.5542) 
(list 2880.125 870.5644) 
(list 2880.125 870.5747) 
(list 2880.125 870.585) 
(list 2880.125 870.5953) 
(list 2880.125 870.6056) 
(list 2880.125 870.6158) 
(list 2880.125 870.6261) 
(list 2880.125 870.6364) 
(list 2880.125 870.6467) 
(list 2880.125 870.6569) 
(list 2880.125 870.6672) 
(list 2880.125 870.6775) 
(list 2880.125 870.6878) 
(list 2880.125 870.6981) 
(list 2880.125 870.7083) 
(list 2880.125 870.7186) 
(list 2880.125 870.7289) 
(list 2880.125 870.7392) 
(list 2880.125 870.7494) 
(list 2880.125 870.7597) 
(list 2880.125 870.77) 
(list 2880 870.77)))
(apply 'command (append '("pline") coords '("c")))
(setq tap9 (ssadd (entlast) tap9))
(command "_mirror" (entlast) "" "2880,900" "2880,901" "No")
(setq tap9 (ssadd (entlast) tap9))
(setq coords (list 
(list 2880.5121 870.4) 
(list 2880.5023 870.4) 
(list 2880.5013 870.4103) 
(list 2880.4977 870.4206) 
(list 2880.4917 870.4308) 
(list 2880.4834 870.4411) 
(list 2880.473 870.4514) 
(list 2880.4609 870.4617) 
(list 2880.4474 870.4719) 
(list 2880.433 870.4822) 
(list 2880.418 870.4925) 
(list 2880.4029 870.5028) 
(list 2880.3882 870.5131) 
(list 2880.3743 870.5233) 
(list 2880.3617 870.5336) 
(list 2880.3508 870.5439) 
(list 2880.3418 870.5542) 
(list 2880.3351 870.5644) 
(list 2880.3309 870.5747) 
(list 2880.3294 870.585) 
(list 2880.3306 870.5953) 
(list 2880.3344 870.6056) 
(list 2880.3408 870.6158) 
(list 2880.3496 870.6261) 
(list 2880.3606 870.6364) 
(list 2880.3734 870.6467) 
(list 2880.3876 870.6569) 
(list 2880.4028 870.6672) 
(list 2880.4186 870.6775) 
(list 2880.4345 870.6878) 
(list 2880.45 870.6981) 
(list 2880.4646 870.7083) 
(list 2880.4779 870.7186) 
(list 2880.4894 870.7289) 
(list 2880.4989 870.7392) 
(list 2880.5059 870.7494) 
(list 2880.5104 870.7597) 
(list 2880.5121 870.77) 
(list 2880.5121 870.77)))
(apply 'command (append '("pline") coords '("c")))
(setq tap9 (ssadd (entlast) tap9))
(command "_mirror" (entlast) "" "2880,900" "2880,901" "No")
(setq tap9 (ssadd (entlast) tap9))
(setq coords (list 
(list 2881.102 870.4) 
(list 2880.5121 870.4) 
(list 2880.5121 870.4103) 
(list 2880.5121 870.4206) 
(list 2880.5121 870.4308) 
(list 2880.5121 870.4411) 
(list 2880.5121 870.4514) 
(list 2880.5121 870.4617) 
(list 2880.5121 870.4719) 
(list 2880.5121 870.4822) 
(list 2880.5121 870.4925) 
(list 2880.5121 870.5028) 
(list 2880.5121 870.5131) 
(list 2880.5121 870.5233) 
(list 2880.5121 870.5336) 
(list 2880.5121 870.5439) 
(list 2880.5121 870.5542) 
(list 2880.5121 870.5644) 
(list 2880.5121 870.5747) 
(list 2880.5121 870.585) 
(list 2880.5121 870.5953) 
(list 2880.5121 870.6056) 
(list 2880.5121 870.6158) 
(list 2880.5121 870.6261) 
(list 2880.5121 870.6364) 
(list 2880.5121 870.6467) 
(list 2880.5121 870.6569) 
(list 2880.5121 870.6672) 
(list 2880.5121 870.6775) 
(list 2880.5121 870.6878) 
(list 2880.5121 870.6981) 
(list 2880.5121 870.7083) 
(list 2880.5121 870.7186) 
(list 2880.5121 870.7289) 
(list 2880.5121 870.7392) 
(list 2880.5121 870.7494) 
(list 2880.5121 870.7597) 
(list 2880.5121 870.77) 
(list 2881.102 870.77)))
(apply 'command (append '("pline") coords '("c")))
(setq tap9 (ssadd (entlast) tap9))
(command "_mirror" (entlast) "" "2880,900" "2880,901" "No")
(setq tap9 (ssadd (entlast) tap9))
(setq coords (list 
(list 2880 870.77) 
(list 2880.125 870.77) 
(list 2880.125 870.7803) 
(list 2880.125 870.7906) 
(list 2880.125 870.8008) 
(list 2880.125 870.8111) 
(list 2880.125 870.8214) 
(list 2880.125 870.8317) 
(list 2880.125 870.8419) 
(list 2880.125 870.8522) 
(list 2880.125 870.8625) 
(list 2880.125 870.8728) 
(list 2880.125 870.8831) 
(list 2880.125 870.8933) 
(list 2880.125 870.9036) 
(list 2880.125 870.9139) 
(list 2880.125 870.9242) 
(list 2880.125 870.9344) 
(list 2880.125 870.9447) 
(list 2880.125 870.955) 
(list 2880.125 870.9653) 
(list 2880.125 870.9756) 
(list 2880.125 870.9858) 
(list 2880.125 870.9961) 
(list 2880.125 871.0064) 
(list 2880.125 871.0167) 
(list 2880.125 871.0269) 
(list 2880.125 871.0372) 
(list 2880.125 871.0475) 
(list 2880.125 871.0578) 
(list 2880.125 871.0681) 
(list 2880.125 871.0783) 
(list 2880.125 871.0886) 
(list 2880.125 871.0989) 
(list 2880.125 871.1092) 
(list 2880.125 871.1194) 
(list 2880.125 871.1297) 
(list 2880.125 871.14) 
(list 2880 871.14)))
(apply 'command (append '("pline") coords '("c")))
(setq tap9 (ssadd (entlast) tap9))
(command "_mirror" (entlast) "" "2880,900" "2880,901" "No")
(setq tap9 (ssadd (entlast) tap9))
(setq coords (list 
(list 2880.5218 870.77) 
(list 2880.5121 870.77) 
(list 2880.5109 870.7803) 
(list 2880.507 870.7906) 
(list 2880.5003 870.8008) 
(list 2880.4911 870.8111) 
(list 2880.4797 870.8214) 
(list 2880.4664 870.8317) 
(list 2880.4516 870.8419) 
(list 2880.4357 870.8522) 
(list 2880.4192 870.8625) 
(list 2880.4027 870.8728) 
(list 2880.3866 870.8831) 
(list 2880.3714 870.8933) 
(list 2880.3576 870.9036) 
(list 2880.3456 870.9139) 
(list 2880.3358 870.9242) 
(list 2880.3284 870.9344) 
(list 2880.3239 870.9447) 
(list 2880.3222 870.955) 
(list 2880.3235 870.9653) 
(list 2880.3277 870.9756) 
(list 2880.3347 870.9858) 
(list 2880.3444 870.9961) 
(list 2880.3564 871.0064) 
(list 2880.3704 871.0167) 
(list 2880.3859 871.0269) 
(list 2880.4026 871.0372) 
(list 2880.4199 871.0475) 
(list 2880.4372 871.0578) 
(list 2880.4541 871.0681) 
(list 2880.4701 871.0783) 
(list 2880.4846 871.0886) 
(list 2880.4972 871.0989) 
(list 2880.5075 871.1092) 
(list 2880.5152 871.1194) 
(list 2880.52 871.1297) 
(list 2880.5218 871.14) 
(list 2880.5218 871.14)))
(apply 'command (append '("pline") coords '("c")))
(setq tap9 (ssadd (entlast) tap9))
(command "_mirror" (entlast) "" "2880,900" "2880,901" "No")
(setq tap9 (ssadd (entlast) tap9))
(setq coords (list 
(list 2881.102 870.77) 
(list 2880.5218 870.77) 
(list 2880.5218 870.7803) 
(list 2880.5218 870.7906) 
(list 2880.5218 870.8008) 
(list 2880.5218 870.8111) 
(list 2880.5218 870.8214) 
(list 2880.5218 870.8317) 
(list 2880.5218 870.8419) 
(list 2880.5218 870.8522) 
(list 2880.5218 870.8625) 
(list 2880.5218 870.8728) 
(list 2880.5218 870.8831) 
(list 2880.5218 870.8933) 
(list 2880.5218 870.9036) 
(list 2880.5218 870.9139) 
(list 2880.5218 870.9242) 
(list 2880.5218 870.9344) 
(list 2880.5218 870.9447) 
(list 2880.5218 870.955) 
(list 2880.5218 870.9653) 
(list 2880.5218 870.9756) 
(list 2880.5218 870.9858) 
(list 2880.5218 870.9961) 
(list 2880.5218 871.0064) 
(list 2880.5218 871.0167) 
(list 2880.5218 871.0269) 
(list 2880.5218 871.0372) 
(list 2880.5218 871.0475) 
(list 2880.5218 871.0578) 
(list 2880.5218 871.0681) 
(list 2880.5218 871.0783) 
(list 2880.5218 871.0886) 
(list 2880.5218 871.0989) 
(list 2880.5218 871.1092) 
(list 2880.5218 871.1194) 
(list 2880.5218 871.1297) 
(list 2880.5218 871.14) 
(list 2881.102 871.14)))
(apply 'command (append '("pline") coords '("c")))
(setq tap9 (ssadd (entlast) tap9))
(command "_mirror" (entlast) "" "2880,900" "2880,901" "No")
(setq tap9 (ssadd (entlast) tap9))
(setq coords (list 
(list 2880 871.14) 
(list 2880.125 871.14) 
(list 2880.125 871.1503) 
(list 2880.125 871.1606) 
(list 2880.125 871.1708) 
(list 2880.125 871.1811) 
(list 2880.125 871.1914) 
(list 2880.125 871.2017) 
(list 2880.125 871.2119) 
(list 2880.125 871.2222) 
(list 2880.125 871.2325) 
(list 2880.125 871.2428) 
(list 2880.125 871.2531) 
(list 2880.125 871.2633) 
(list 2880.125 871.2736) 
(list 2880.125 871.2839) 
(list 2880.125 871.2942) 
(list 2880.125 871.3044) 
(list 2880.125 871.3147) 
(list 2880.125 871.325) 
(list 2880.125 871.3353) 
(list 2880.125 871.3456) 
(list 2880.125 871.3558) 
(list 2880.125 871.3661) 
(list 2880.125 871.3764) 
(list 2880.125 871.3867) 
(list 2880.125 871.3969) 
(list 2880.125 871.4072) 
(list 2880.125 871.4175) 
(list 2880.125 871.4278) 
(list 2880.125 871.4381) 
(list 2880.125 871.4483) 
(list 2880.125 871.4586) 
(list 2880.125 871.4689) 
(list 2880.125 871.4792) 
(list 2880.125 871.4894) 
(list 2880.125 871.4997) 
(list 2880.125 871.51) 
(list 2880 871.51)))
(apply 'command (append '("pline") coords '("c")))
(setq tap9 (ssadd (entlast) tap9))
(command "_mirror" (entlast) "" "2880,900" "2880,901" "No")
(setq tap9 (ssadd (entlast) tap9))
(setq coords (list 
(list 2880.5315 871.14) 
(list 2880.5218 871.14) 
(list 2880.5205 871.1503) 
(list 2880.5162 871.1606) 
(list 2880.5089 871.1708) 
(list 2880.4989 871.1811) 
(list 2880.4864 871.1914) 
(list 2880.4719 871.2017) 
(list 2880.4558 871.2119) 
(list 2880.4385 871.2222) 
(list 2880.4205 871.2325) 
(list 2880.4025 871.2428) 
(list 2880.385 871.2531) 
(list 2880.3684 871.2633) 
(list 2880.3534 871.2736) 
(list 2880.3403 871.2839) 
(list 2880.3297 871.2942) 
(list 2880.3218 871.3044) 
(list 2880.3168 871.3147) 
(list 2880.315 871.325) 
(list 2880.3164 871.3353) 
(list 2880.321 871.3456) 
(list 2880.3287 871.3558) 
(list 2880.3392 871.3661) 
(list 2880.3522 871.3764) 
(list 2880.3674 871.3867) 
(list 2880.3843 871.3969) 
(list 2880.4024 871.4072) 
(list 2880.4212 871.4175) 
(list 2880.44 871.4278) 
(list 2880.4583 871.4381) 
(list 2880.4756 871.4483) 
(list 2880.4913 871.4586) 
(list 2880.5049 871.4689) 
(list 2880.5161 871.4792) 
(list 2880.5244 871.4894) 
(list 2880.5296 871.4997) 
(list 2880.5315 871.51) 
(list 2880.5315 871.51)))
(apply 'command (append '("pline") coords '("c")))
(setq tap9 (ssadd (entlast) tap9))
(command "_mirror" (entlast) "" "2880,900" "2880,901" "No")
(setq tap9 (ssadd (entlast) tap9))
(setq coords (list 
(list 2881.102 871.14) 
(list 2880.5315 871.14) 
(list 2880.5315 871.1503) 
(list 2880.5315 871.1606) 
(list 2880.5315 871.1708) 
(list 2880.5315 871.1811) 
(list 2880.5315 871.1914) 
(list 2880.5315 871.2017) 
(list 2880.5315 871.2119) 
(list 2880.5315 871.2222) 
(list 2880.5315 871.2325) 
(list 2880.5315 871.2428) 
(list 2880.5315 871.2531) 
(list 2880.5315 871.2633) 
(list 2880.5315 871.2736) 
(list 2880.5315 871.2839) 
(list 2880.5315 871.2942) 
(list 2880.5315 871.3044) 
(list 2880.5315 871.3147) 
(list 2880.5315 871.325) 
(list 2880.5315 871.3353) 
(list 2880.5315 871.3456) 
(list 2880.5315 871.3558) 
(list 2880.5315 871.3661) 
(list 2880.5315 871.3764) 
(list 2880.5315 871.3867) 
(list 2880.5315 871.3969) 
(list 2880.5315 871.4072) 
(list 2880.5315 871.4175) 
(list 2880.5315 871.4278) 
(list 2880.5315 871.4381) 
(list 2880.5315 871.4483) 
(list 2880.5315 871.4586) 
(list 2880.5315 871.4689) 
(list 2880.5315 871.4792) 
(list 2880.5315 871.4894) 
(list 2880.5315 871.4997) 
(list 2880.5315 871.51) 
(list 2881.102 871.51)))
(apply 'command (append '("pline") coords '("c")))
(setq tap9 (ssadd (entlast) tap9))
(command "_mirror" (entlast) "" "2880,900" "2880,901" "No")
(setq tap9 (ssadd (entlast) tap9))
(setq coords (list 
(list 2880 871.51) 
(list 2880.125 871.51) 
(list 2880.125 871.5203) 
(list 2880.125 871.5306) 
(list 2880.125 871.5408) 
(list 2880.125 871.5511) 
(list 2880.125 871.5614) 
(list 2880.125 871.5717) 
(list 2880.125 871.5819) 
(list 2880.125 871.5922) 
(list 2880.125 871.6025) 
(list 2880.125 871.6128) 
(list 2880.125 871.6231) 
(list 2880.125 871.6333) 
(list 2880.125 871.6436) 
(list 2880.125 871.6539) 
(list 2880.125 871.6642) 
(list 2880.125 871.6744) 
(list 2880.125 871.6847) 
(list 2880.125 871.695) 
(list 2880.125 871.7053) 
(list 2880.125 871.7156) 
(list 2880.125 871.7258) 
(list 2880.125 871.7361) 
(list 2880.125 871.7464) 
(list 2880.125 871.7567) 
(list 2880.125 871.7669) 
(list 2880.125 871.7772) 
(list 2880.125 871.7875) 
(list 2880.125 871.7978) 
(list 2880.125 871.8081) 
(list 2880.125 871.8183) 
(list 2880.125 871.8286) 
(list 2880.125 871.8389) 
(list 2880.125 871.8492) 
(list 2880.125 871.8594) 
(list 2880.125 871.8697) 
(list 2880.125 871.88) 
(list 2880 871.88)))
(apply 'command (append '("pline") coords '("c")))
(setq tap9 (ssadd (entlast) tap9))
(command "_mirror" (entlast) "" "2880,900" "2880,901" "No")
(setq tap9 (ssadd (entlast) tap9))
(setq coords (list 
(list 2880.5413 871.51) 
(list 2880.5315 871.51) 
(list 2880.5301 871.5203) 
(list 2880.5254 871.5306) 
(list 2880.5175 871.5408) 
(list 2880.5066 871.5511) 
(list 2880.4931 871.5614) 
(list 2880.4774 871.5717) 
(list 2880.4599 871.5819) 
(list 2880.4412 871.5922) 
(list 2880.4218 871.6025) 
(list 2880.4023 871.6128) 
(list 2880.3833 871.6231) 
(list 2880.3654 871.6333) 
(list 2880.3492 871.6436) 
(list 2880.3351 871.6539) 
(list 2880.3236 871.6642) 
(list 2880.3151 871.6744) 
(list 2880.3097 871.6847) 
(list 2880.3078 871.695) 
(list 2880.3093 871.7053) 
(list 2880.3143 871.7156) 
(list 2880.3226 871.7258) 
(list 2880.334 871.7361) 
(list 2880.3481 871.7464) 
(list 2880.3645 871.7567) 
(list 2880.3827 871.7669) 
(list 2880.4022 871.7772) 
(list 2880.4224 871.7875) 
(list 2880.4427 871.7978) 
(list 2880.4625 871.8081) 
(list 2880.4811 871.8183) 
(list 2880.498 871.8286) 
(list 2880.5127 871.8389) 
(list 2880.5247 871.8492) 
(list 2880.5336 871.8594) 
(list 2880.5392 871.8697) 
(list 2880.5413 871.88) 
(list 2880.5413 871.88)))
(apply 'command (append '("pline") coords '("c")))
(setq tap9 (ssadd (entlast) tap9))
(command "_mirror" (entlast) "" "2880,900" "2880,901" "No")
(setq tap9 (ssadd (entlast) tap9))
(setq coords (list 
(list 2881.102 871.51) 
(list 2880.5413 871.51) 
(list 2880.5413 871.5203) 
(list 2880.5413 871.5306) 
(list 2880.5413 871.5408) 
(list 2880.5413 871.5511) 
(list 2880.5413 871.5614) 
(list 2880.5413 871.5717) 
(list 2880.5413 871.5819) 
(list 2880.5413 871.5922) 
(list 2880.5413 871.6025) 
(list 2880.5413 871.6128) 
(list 2880.5413 871.6231) 
(list 2880.5413 871.6333) 
(list 2880.5413 871.6436) 
(list 2880.5413 871.6539) 
(list 2880.5413 871.6642) 
(list 2880.5413 871.6744) 
(list 2880.5413 871.6847) 
(list 2880.5413 871.695) 
(list 2880.5413 871.7053) 
(list 2880.5413 871.7156) 
(list 2880.5413 871.7258) 
(list 2880.5413 871.7361) 
(list 2880.5413 871.7464) 
(list 2880.5413 871.7567) 
(list 2880.5413 871.7669) 
(list 2880.5413 871.7772) 
(list 2880.5413 871.7875) 
(list 2880.5413 871.7978) 
(list 2880.5413 871.8081) 
(list 2880.5413 871.8183) 
(list 2880.5413 871.8286) 
(list 2880.5413 871.8389) 
(list 2880.5413 871.8492) 
(list 2880.5413 871.8594) 
(list 2880.5413 871.8697) 
(list 2880.5413 871.88) 
(list 2881.102 871.88)))
(apply 'command (append '("pline") coords '("c")))
(setq tap9 (ssadd (entlast) tap9))
(command "_mirror" (entlast) "" "2880,900" "2880,901" "No")
(setq tap9 (ssadd (entlast) tap9))
(setq coords (list 
(list 2880 871.88) 
(list 2880.125 871.88) 
(list 2880.125 871.8903) 
(list 2880.125 871.9006) 
(list 2880.125 871.9108) 
(list 2880.125 871.9211) 
(list 2880.125 871.9314) 
(list 2880.125 871.9417) 
(list 2880.125 871.9519) 
(list 2880.125 871.9622) 
(list 2880.125 871.9725) 
(list 2880.125 871.9828) 
(list 2880.125 871.9931) 
(list 2880.125 872.0033) 
(list 2880.125 872.0136) 
(list 2880.125 872.0239) 
(list 2880.125 872.0342) 
(list 2880.125 872.0444) 
(list 2880.125 872.0547) 
(list 2880.125 872.065) 
(list 2880.125 872.0753) 
(list 2880.125 872.0856) 
(list 2880.125 872.0958) 
(list 2880.125 872.1061) 
(list 2880.125 872.1164) 
(list 2880.125 872.1267) 
(list 2880.125 872.1369) 
(list 2880.125 872.1472) 
(list 2880.125 872.1575) 
(list 2880.125 872.1678) 
(list 2880.125 872.1781) 
(list 2880.125 872.1883) 
(list 2880.125 872.1986) 
(list 2880.125 872.2089) 
(list 2880.125 872.2192) 
(list 2880.125 872.2294) 
(list 2880.125 872.2397) 
(list 2880.125 872.25) 
(list 2880 872.25)))
(apply 'command (append '("pline") coords '("c")))
(setq tap9 (ssadd (entlast) tap9))
(command "_mirror" (entlast) "" "2880,900" "2880,901" "No")
(setq tap9 (ssadd (entlast) tap9))
(setq coords (list 
(list 2880.551 871.88) 
(list 2880.5413 871.88) 
(list 2880.5397 871.8903) 
(list 2880.5346 871.9006) 
(list 2880.5261 871.9108) 
(list 2880.5144 871.9211) 
(list 2880.4999 871.9314) 
(list 2880.4829 871.9417) 
(list 2880.4641 871.9519) 
(list 2880.4439 871.9622) 
(list 2880.423 871.9725) 
(list 2880.4021 871.9828) 
(list 2880.3817 871.9931) 
(list 2880.3625 872.0033) 
(list 2880.345 872.0136) 
(list 2880.3299 872.0239) 
(list 2880.3176 872.0342) 
(list 2880.3084 872.0444) 
(list 2880.3027 872.0547) 
(list 2880.3006 872.065) 
(list 2880.3023 872.0753) 
(list 2880.3076 872.0856) 
(list 2880.3165 872.0958) 
(list 2880.3287 872.1061) 
(list 2880.3439 872.1164) 
(list 2880.3615 872.1267) 
(list 2880.3811 872.1369) 
(list 2880.402 872.1472) 
(list 2880.4237 872.1575) 
(list 2880.4454 872.1678) 
(list 2880.4666 872.1781) 
(list 2880.4866 872.1883) 
(list 2880.5047 872.1986) 
(list 2880.5204 872.2089) 
(list 2880.5333 872.2192) 
(list 2880.5428 872.2294) 
(list 2880.5488 872.2397) 
(list 2880.551 872.25) 
(list 2880.551 872.25)))
(apply 'command (append '("pline") coords '("c")))
(setq tap9 (ssadd (entlast) tap9))
(command "_mirror" (entlast) "" "2880,900" "2880,901" "No")
(setq tap9 (ssadd (entlast) tap9))
(setq coords (list 
(list 2881.102 871.88) 
(list 2880.551 871.88) 
(list 2880.551 871.8903) 
(list 2880.551 871.9006) 
(list 2880.551 871.9108) 
(list 2880.551 871.9211) 
(list 2880.551 871.9314) 
(list 2880.551 871.9417) 
(list 2880.551 871.9519) 
(list 2880.551 871.9622) 
(list 2880.551 871.9725) 
(list 2880.551 871.9828) 
(list 2880.551 871.9931) 
(list 2880.551 872.0033) 
(list 2880.551 872.0136) 
(list 2880.551 872.0239) 
(list 2880.551 872.0342) 
(list 2880.551 872.0444) 
(list 2880.551 872.0547) 
(list 2880.551 872.065) 
(list 2880.551 872.0753) 
(list 2880.551 872.0856) 
(list 2880.551 872.0958) 
(list 2880.551 872.1061) 
(list 2880.551 872.1164) 
(list 2880.551 872.1267) 
(list 2880.551 872.1369) 
(list 2880.551 872.1472) 
(list 2880.551 872.1575) 
(list 2880.551 872.1678) 
(list 2880.551 872.1781) 
(list 2880.551 872.1883) 
(list 2880.551 872.1986) 
(list 2880.551 872.2089) 
(list 2880.551 872.2192) 
(list 2880.551 872.2294) 
(list 2880.551 872.2397) 
(list 2880.551 872.25) 
(list 2881.102 872.25)))
(apply 'command (append '("pline") coords '("c")))
(setq tap9 (ssadd (entlast) tap9))
(command "_mirror" (entlast) "" "2880,900" "2880,901" "No")
(setq tap9 (ssadd (entlast) tap9))
(command "_block" "blktap9" "2880,900" tap9 "")
(command "_insert" "blktap9" "2880,900" "1" "1" "0")
(command "_insert" "blktap9" "2880,900" "1" "1" "180")
(setq uc9 nil)
(setq uc9 (ssadd))
(setq coords (list 
(list 0 -0.185) 
(list 0.125 -0.185) 
(list 0.125 -0.17472) 
(list 0.125 -0.16444) 
(list 0.125 -0.15417) 
(list 0.125 -0.14389) 
(list 0.125 -0.13361) 
(list 0.125 -0.12333) 
(list 0.125 -0.11306) 
(list 0.125 -0.10278) 
(list 0.125 -0.0925) 
(list 0.125 -0.082222) 
(list 0.125 -0.071944) 
(list 0.125 -0.061667) 
(list 0.125 -0.051389) 
(list 0.125 -0.041111) 
(list 0.125 -0.030833) 
(list 0.125 -0.020556) 
(list 0.125 -0.010278) 
(list 0.125 0) 
(list 0.125 0.010278) 
(list 0.125 0.020556) 
(list 0.125 0.030833) 
(list 0.125 0.041111) 
(list 0.125 0.051389) 
(list 0.125 0.061667) 
(list 0.125 0.071944) 
(list 0.125 0.082222) 
(list 0.125 0.0925) 
(list 0.125 0.10278) 
(list 0.125 0.11306) 
(list 0.125 0.12333) 
(list 0.125 0.13361) 
(list 0.125 0.14389) 
(list 0.125 0.15417) 
(list 0.125 0.16444) 
(list 0.125 0.17472) 
(list 0.125 0.185) 
(list 0 0.185)))
(apply 'command (append '("pline") coords '("c")))
(setq uc9 (ssadd (entlast) uc9))
(setq coords (list 
(list 1.102 -0.185) 
(list 0.551 -0.185) 
(list 0.54907 -0.17472) 
(list 0.54334 -0.16444) 
(list 0.53399 -0.15417) 
(list 0.52129 -0.14389) 
(list 0.50563 -0.13361) 
(list 0.4875 -0.12333) 
(list 0.46744 -0.11306) 
(list 0.44605 -0.10278) 
(list 0.424 -0.0925) 
(list 0.40195 -0.082222) 
(list 0.38056 -0.071944) 
(list 0.3605 -0.061667) 
(list 0.34237 -0.051389) 
(list 0.32671 -0.041111) 
(list 0.31401 -0.030833) 
(list 0.30466 -0.020556) 
(list 0.29893 -0.010278) 
(list 0.297 0) 
(list 0.29893 0.010278) 
(list 0.30466 0.020556) 
(list 0.31401 0.030833) 
(list 0.32671 0.041111) 
(list 0.34237 0.051389) 
(list 0.3605 0.061667) 
(list 0.38056 0.071944) 
(list 0.40195 0.082222) 
(list 0.424 0.0925) 
(list 0.44605 0.10278) 
(list 0.46744 0.11306) 
(list 0.4875 0.12333) 
(list 0.50563 0.13361) 
(list 0.52129 0.14389) 
(list 0.53399 0.15417) 
(list 0.54334 0.16444) 
(list 0.54907 0.17472) 
(list 0.551 0.185) 
(list 1.102 0.185)))
(apply 'command (append '("pline") coords '("c")))
(setq uc9 (ssadd (entlast) uc9))
(command "_block" "blkuc9" "0,0.185" uc9 "")
(command "_insert" "blkuc9" "2880,872.62" "1" "1" "0")
(command "_insert" "blkuc9" "2880,872.25" "1" "1" "180")
(command "_insert" "blkuc9" "2880,872.99" "1" "1" "0")
(command "_insert" "blkuc9" "2880,872.62" "1" "1" "180")
(command "_insert" "blkuc9" "2880,873.36" "1" "1" "0")
(command "_insert" "blkuc9" "2880,872.99" "1" "1" "180")
(command "_insert" "blkuc9" "2880,873.73" "1" "1" "0")
(command "_insert" "blkuc9" "2880,873.36" "1" "1" "180")
(command "_insert" "blkuc9" "2880,874.1" "1" "1" "0")
(command "_insert" "blkuc9" "2880,873.73" "1" "1" "180")
(command "_insert" "blkuc9" "2880,874.47" "1" "1" "0")
(command "_insert" "blkuc9" "2880,874.1" "1" "1" "180")
(command "_insert" "blkuc9" "2880,874.84" "1" "1" "0")
(command "_insert" "blkuc9" "2880,874.47" "1" "1" "180")
(command "_insert" "blkuc9" "2880,875.21" "1" "1" "0")
(command "_insert" "blkuc9" "2880,874.84" "1" "1" "180")
(command "_insert" "blkuc9" "2880,875.58" "1" "1" "0")
(command "_insert" "blkuc9" "2880,875.21" "1" "1" "180")
(command "_insert" "blkuc9" "2880,875.95" "1" "1" "0")
(command "_insert" "blkuc9" "2880,875.58" "1" "1" "180")
(command "_insert" "blkuc9" "2880,876.32" "1" "1" "0")
(command "_insert" "blkuc9" "2880,875.95" "1" "1" "180")
(command "_insert" "blkuc9" "2880,876.69" "1" "1" "0")
(command "_insert" "blkuc9" "2880,876.32" "1" "1" "180")
(command "_insert" "blkuc9" "2880,877.06" "1" "1" "0")
(command "_insert" "blkuc9" "2880,876.69" "1" "1" "180")
(command "_insert" "blkuc9" "2880,877.43" "1" "1" "0")
(command "_insert" "blkuc9" "2880,877.06" "1" "1" "180")
(command "_insert" "blkuc9" "2880,877.8" "1" "1" "0")
(command "_insert" "blkuc9" "2880,877.43" "1" "1" "180")
(command "_insert" "blkuc9" "2880,878.17" "1" "1" "0")
(command "_insert" "blkuc9" "2880,877.8" "1" "1" "180")
(command "_insert" "blkuc9" "2880,878.54" "1" "1" "0")
(command "_insert" "blkuc9" "2880,878.17" "1" "1" "180")
(command "_insert" "blkuc9" "2880,878.91" "1" "1" "0")
(command "_insert" "blkuc9" "2880,878.54" "1" "1" "180")
(command "_insert" "blkuc9" "2880,879.28" "1" "1" "0")
(command "_insert" "blkuc9" "2880,878.91" "1" "1" "180")
(command "_insert" "blkuc9" "2880,879.65" "1" "1" "0")
(command "_insert" "blkuc9" "2880,879.28" "1" "1" "180")
(command "_insert" "blkuc9" "2880,880.02" "1" "1" "0")
(command "_insert" "blkuc9" "2880,879.65" "1" "1" "180")
(command "_insert" "blkuc9" "2880,880.39" "1" "1" "0")
(command "_insert" "blkuc9" "2880,880.02" "1" "1" "180")
(command "_insert" "blkuc9" "2880,880.76" "1" "1" "0")
(command "_insert" "blkuc9" "2880,880.39" "1" "1" "180")
(command "_insert" "blkuc9" "2880,881.13" "1" "1" "0")
(command "_insert" "blkuc9" "2880,880.76" "1" "1" "180")
(command "_insert" "blkuc9" "2880,881.5" "1" "1" "0")
(command "_insert" "blkuc9" "2880,881.13" "1" "1" "180")
(command "_insert" "blkuc9" "2880,881.87" "1" "1" "0")
(command "_insert" "blkuc9" "2880,881.5" "1" "1" "180")
(command "_insert" "blkuc9" "2880,882.24" "1" "1" "0")
(command "_insert" "blkuc9" "2880,881.87" "1" "1" "180")
(command "_insert" "blkuc9" "2880,882.61" "1" "1" "0")
(command "_insert" "blkuc9" "2880,882.24" "1" "1" "180")
(command "_insert" "blkuc9" "2880,882.98" "1" "1" "0")
(command "_insert" "blkuc9" "2880,882.61" "1" "1" "180")
(command "_insert" "blkuc9" "2880,883.35" "1" "1" "0")
(command "_insert" "blkuc9" "2880,882.98" "1" "1" "180")
(command "_insert" "blkuc9" "2880,883.72" "1" "1" "0")
(command "_insert" "blkuc9" "2880,883.35" "1" "1" "180")
(command "_insert" "blkuc9" "2880,884.09" "1" "1" "0")
(command "_insert" "blkuc9" "2880,883.72" "1" "1" "180")
(command "_insert" "blkuc9" "2880,884.46" "1" "1" "0")
(command "_insert" "blkuc9" "2880,884.09" "1" "1" "180")
(command "_insert" "blkuc9" "2880,884.83" "1" "1" "0")
(command "_insert" "blkuc9" "2880,884.46" "1" "1" "180")
(command "_insert" "blkuc9" "2880,885.2" "1" "1" "0")
(command "_insert" "blkuc9" "2880,884.83" "1" "1" "180")
(command "_insert" "blkuc9" "2880,885.57" "1" "1" "0")
(command "_insert" "blkuc9" "2880,885.2" "1" "1" "180")
(command "_insert" "blkuc9" "2880,885.94" "1" "1" "0")
(command "_insert" "blkuc9" "2880,885.57" "1" "1" "180")
(command "_insert" "blkuc9" "2880,886.31" "1" "1" "0")
(command "_insert" "blkuc9" "2880,885.94" "1" "1" "180")
(command "_insert" "blkuc9" "2880,886.68" "1" "1" "0")
(command "_insert" "blkuc9" "2880,886.31" "1" "1" "180")
(command "_insert" "blkuc9" "2880,887.05" "1" "1" "0")
(command "_insert" "blkuc9" "2880,886.68" "1" "1" "180")
(command "_insert" "blkuc9" "2880,887.42" "1" "1" "0")
(command "_insert" "blkuc9" "2880,887.05" "1" "1" "180")
(command "_insert" "blkuc9" "2880,887.79" "1" "1" "0")
(command "_insert" "blkuc9" "2880,887.42" "1" "1" "180")
(command "_insert" "blkuc9" "2880,888.16" "1" "1" "0")
(command "_insert" "blkuc9" "2880,887.79" "1" "1" "180")
(command "_insert" "blkuc9" "2880,888.53" "1" "1" "0")
(command "_insert" "blkuc9" "2880,888.16" "1" "1" "180")
(command "_insert" "blkuc9" "2880,888.9" "1" "1" "0")
(command "_insert" "blkuc9" "2880,888.53" "1" "1" "180")
(command "_insert" "blkuc9" "2880,889.27" "1" "1" "0")
(command "_insert" "blkuc9" "2880,888.9" "1" "1" "180")
(command "_insert" "blkuc9" "2880,889.64" "1" "1" "0")
(command "_insert" "blkuc9" "2880,889.27" "1" "1" "180")
(command "_insert" "blkuc9" "2880,890.01" "1" "1" "0")
(command "_insert" "blkuc9" "2880,889.64" "1" "1" "180")
(command "_insert" "blkuc9" "2880,890.38" "1" "1" "0")
(command "_insert" "blkuc9" "2880,890.01" "1" "1" "180")
(command "_insert" "blkuc9" "2880,890.75" "1" "1" "0")
(command "_insert" "blkuc9" "2880,890.38" "1" "1" "180")
(command "_insert" "blkuc9" "2880,891.12" "1" "1" "0")
(command "_insert" "blkuc9" "2880,890.75" "1" "1" "180")
(command "_insert" "blkuc9" "2880,891.49" "1" "1" "0")
(command "_insert" "blkuc9" "2880,891.12" "1" "1" "180")
(command "_insert" "blkuc9" "2880,891.86" "1" "1" "0")
(command "_insert" "blkuc9" "2880,891.49" "1" "1" "180")
(command "_insert" "blkuc9" "2880,892.23" "1" "1" "0")
(command "_insert" "blkuc9" "2880,891.86" "1" "1" "180")
(command "_insert" "blkuc9" "2880,892.6" "1" "1" "0")
(command "_insert" "blkuc9" "2880,892.23" "1" "1" "180")
(command "_insert" "blkuc9" "2880,892.97" "1" "1" "0")
(command "_insert" "blkuc9" "2880,892.6" "1" "1" "180")
(command "_insert" "blkuc9" "2880,893.34" "1" "1" "0")
(command "_insert" "blkuc9" "2880,892.97" "1" "1" "180")
(command "_insert" "blkuc9" "2880,893.71" "1" "1" "0")
(command "_insert" "blkuc9" "2880,893.34" "1" "1" "180")
(command "_insert" "blkuc9" "2880,894.08" "1" "1" "0")
(command "_insert" "blkuc9" "2880,893.71" "1" "1" "180")
(command "_insert" "blkuc9" "2880,894.45" "1" "1" "0")
(command "_insert" "blkuc9" "2880,894.08" "1" "1" "180")
(command "_insert" "blkuc9" "2880,894.82" "1" "1" "0")
(command "_insert" "blkuc9" "2880,894.45" "1" "1" "180")
(command "_insert" "blkuc9" "2880,895.19" "1" "1" "0")
(command "_insert" "blkuc9" "2880,894.82" "1" "1" "180")
(command "_insert" "blkuc9" "2880,895.56" "1" "1" "0")
(command "_insert" "blkuc9" "2880,895.19" "1" "1" "180")
(command "_insert" "blkuc9" "2880,895.93" "1" "1" "0")
(command "_insert" "blkuc9" "2880,895.56" "1" "1" "180")
(command "_insert" "blkuc9" "2880,896.3" "1" "1" "0")
(command "_insert" "blkuc9" "2880,895.93" "1" "1" "180")
(command "_insert" "blkuc9" "2880,896.67" "1" "1" "0")
(command "_insert" "blkuc9" "2880,896.3" "1" "1" "180")
(command "_insert" "blkuc9" "2880,897.04" "1" "1" "0")
(command "_insert" "blkuc9" "2880,896.67" "1" "1" "180")
(command "_insert" "blkuc9" "2880,897.41" "1" "1" "0")
(command "_insert" "blkuc9" "2880,897.04" "1" "1" "180")
(command "_insert" "blkuc9" "2880,897.78" "1" "1" "0")
(command "_insert" "blkuc9" "2880,897.41" "1" "1" "180")
(command "_insert" "blkuc9" "2880,898.15" "1" "1" "0")
(command "_insert" "blkuc9" "2880,897.78" "1" "1" "180")
(command "_insert" "blkuc9" "2880,898.52" "1" "1" "0")
(command "_insert" "blkuc9" "2880,898.15" "1" "1" "180")
(command "_insert" "blkuc9" "2880,898.89" "1" "1" "0")
(command "_insert" "blkuc9" "2880,898.52" "1" "1" "180")
(command "_insert" "blkuc9" "2880,899.26" "1" "1" "0")
(command "_insert" "blkuc9" "2880,898.89" "1" "1" "180")
(command "_insert" "blkuc9" "2880,899.63" "1" "1" "0")
(command "_insert" "blkuc9" "2880,899.26" "1" "1" "180")
(command "_insert" "blkuc9" "2880,900" "1" "1" "0")
(command "_insert" "blkuc9" "2880,899.63" "1" "1" "180")
(command "_insert" "blkuc9" "2880,900.37" "1" "1" "0")
(command "_insert" "blkuc9" "2880,900" "1" "1" "180")
(command "_insert" "blkuc9" "2880,900.74" "1" "1" "0")
(command "_insert" "blkuc9" "2880,900.37" "1" "1" "180")
(command "_insert" "blkuc9" "2880,901.11" "1" "1" "0")
(command "_insert" "blkuc9" "2880,900.74" "1" "1" "180")
(command "_insert" "blkuc9" "2880,901.48" "1" "1" "0")
(command "_insert" "blkuc9" "2880,901.11" "1" "1" "180")
(command "_insert" "blkuc9" "2880,901.85" "1" "1" "0")
(command "_insert" "blkuc9" "2880,901.48" "1" "1" "180")
(command "_insert" "blkuc9" "2880,902.22" "1" "1" "0")
(command "_insert" "blkuc9" "2880,901.85" "1" "1" "180")
(command "_insert" "blkuc9" "2880,902.59" "1" "1" "0")
(command "_insert" "blkuc9" "2880,902.22" "1" "1" "180")
(command "_insert" "blkuc9" "2880,902.96" "1" "1" "0")
(command "_insert" "blkuc9" "2880,902.59" "1" "1" "180")
(command "_insert" "blkuc9" "2880,903.33" "1" "1" "0")
(command "_insert" "blkuc9" "2880,902.96" "1" "1" "180")
(command "_insert" "blkuc9" "2880,903.7" "1" "1" "0")
(command "_insert" "blkuc9" "2880,903.33" "1" "1" "180")
(command "_insert" "blkuc9" "2880,904.07" "1" "1" "0")
(command "_insert" "blkuc9" "2880,903.7" "1" "1" "180")
(command "_insert" "blkuc9" "2880,904.44" "1" "1" "0")
(command "_insert" "blkuc9" "2880,904.07" "1" "1" "180")
(command "_insert" "blkuc9" "2880,904.81" "1" "1" "0")
(command "_insert" "blkuc9" "2880,904.44" "1" "1" "180")
(command "_insert" "blkuc9" "2880,905.18" "1" "1" "0")
(command "_insert" "blkuc9" "2880,904.81" "1" "1" "180")
(command "_insert" "blkuc9" "2880,905.55" "1" "1" "0")
(command "_insert" "blkuc9" "2880,905.18" "1" "1" "180")
(command "_insert" "blkuc9" "2880,905.92" "1" "1" "0")
(command "_insert" "blkuc9" "2880,905.55" "1" "1" "180")
(command "_insert" "blkuc9" "2880,906.29" "1" "1" "0")
(command "_insert" "blkuc9" "2880,905.92" "1" "1" "180")
(command "_insert" "blkuc9" "2880,906.66" "1" "1" "0")
(command "_insert" "blkuc9" "2880,906.29" "1" "1" "180")
(command "_insert" "blkuc9" "2880,907.03" "1" "1" "0")
(command "_insert" "blkuc9" "2880,906.66" "1" "1" "180")
(command "_insert" "blkuc9" "2880,907.4" "1" "1" "0")
(command "_insert" "blkuc9" "2880,907.03" "1" "1" "180")
(command "_insert" "blkuc9" "2880,907.77" "1" "1" "0")
(command "_insert" "blkuc9" "2880,907.4" "1" "1" "180")
(command "_insert" "blkuc9" "2880,908.14" "1" "1" "0")
(command "_insert" "blkuc9" "2880,907.77" "1" "1" "180")
(command "_insert" "blkuc9" "2880,908.51" "1" "1" "0")
(command "_insert" "blkuc9" "2880,908.14" "1" "1" "180")
(command "_insert" "blkuc9" "2880,908.88" "1" "1" "0")
(command "_insert" "blkuc9" "2880,908.51" "1" "1" "180")
(command "_insert" "blkuc9" "2880,909.25" "1" "1" "0")
(command "_insert" "blkuc9" "2880,908.88" "1" "1" "180")
(command "_insert" "blkuc9" "2880,909.62" "1" "1" "0")
(command "_insert" "blkuc9" "2880,909.25" "1" "1" "180")
(command "_insert" "blkuc9" "2880,909.99" "1" "1" "0")
(command "_insert" "blkuc9" "2880,909.62" "1" "1" "180")
(command "_insert" "blkuc9" "2880,910.36" "1" "1" "0")
(command "_insert" "blkuc9" "2880,909.99" "1" "1" "180")
(command "_insert" "blkuc9" "2880,910.73" "1" "1" "0")
(command "_insert" "blkuc9" "2880,910.36" "1" "1" "180")
(command "_insert" "blkuc9" "2880,911.1" "1" "1" "0")
(command "_insert" "blkuc9" "2880,910.73" "1" "1" "180")
(command "_insert" "blkuc9" "2880,911.47" "1" "1" "0")
(command "_insert" "blkuc9" "2880,911.1" "1" "1" "180")
(command "_insert" "blkuc9" "2880,911.84" "1" "1" "0")
(command "_insert" "blkuc9" "2880,911.47" "1" "1" "180")
(command "_insert" "blkuc9" "2880,912.21" "1" "1" "0")
(command "_insert" "blkuc9" "2880,911.84" "1" "1" "180")
(command "_insert" "blkuc9" "2880,912.58" "1" "1" "0")
(command "_insert" "blkuc9" "2880,912.21" "1" "1" "180")
(command "_insert" "blkuc9" "2880,912.95" "1" "1" "0")
(command "_insert" "blkuc9" "2880,912.58" "1" "1" "180")
(command "_insert" "blkuc9" "2880,913.32" "1" "1" "0")
(command "_insert" "blkuc9" "2880,912.95" "1" "1" "180")
(command "_insert" "blkuc9" "2880,913.69" "1" "1" "0")
(command "_insert" "blkuc9" "2880,913.32" "1" "1" "180")
(command "_insert" "blkuc9" "2880,914.06" "1" "1" "0")
(command "_insert" "blkuc9" "2880,913.69" "1" "1" "180")
(command "_insert" "blkuc9" "2880,914.43" "1" "1" "0")
(command "_insert" "blkuc9" "2880,914.06" "1" "1" "180")
(command "_insert" "blkuc9" "2880,914.8" "1" "1" "0")
(command "_insert" "blkuc9" "2880,914.43" "1" "1" "180")
(command "_insert" "blkuc9" "2880,915.17" "1" "1" "0")
(command "_insert" "blkuc9" "2880,914.8" "1" "1" "180")
(command "_insert" "blkuc9" "2880,915.54" "1" "1" "0")
(command "_insert" "blkuc9" "2880,915.17" "1" "1" "180")
(command "_insert" "blkuc9" "2880,915.91" "1" "1" "0")
(command "_insert" "blkuc9" "2880,915.54" "1" "1" "180")
(command "_insert" "blkuc9" "2880,916.28" "1" "1" "0")
(command "_insert" "blkuc9" "2880,915.91" "1" "1" "180")
(command "_insert" "blkuc9" "2880,916.65" "1" "1" "0")
(command "_insert" "blkuc9" "2880,916.28" "1" "1" "180")
(command "_insert" "blkuc9" "2880,917.02" "1" "1" "0")
(command "_insert" "blkuc9" "2880,916.65" "1" "1" "180")
(command "_insert" "blkuc9" "2880,917.39" "1" "1" "0")
(command "_insert" "blkuc9" "2880,917.02" "1" "1" "180")
(command "_insert" "blkuc9" "2880,917.76" "1" "1" "0")
(command "_insert" "blkuc9" "2880,917.39" "1" "1" "180")
(command "_insert" "blkuc9" "2880,918.13" "1" "1" "0")
(command "_insert" "blkuc9" "2880,917.76" "1" "1" "180")
(command "_insert" "blkuc9" "2880,918.5" "1" "1" "0")
(command "_insert" "blkuc9" "2880,918.13" "1" "1" "180")
(command "_insert" "blkuc9" "2880,918.87" "1" "1" "0")
(command "_insert" "blkuc9" "2880,918.5" "1" "1" "180")
(command "_insert" "blkuc9" "2880,919.24" "1" "1" "0")
(command "_insert" "blkuc9" "2880,918.87" "1" "1" "180")
(command "_insert" "blkuc9" "2880,919.61" "1" "1" "0")
(command "_insert" "blkuc9" "2880,919.24" "1" "1" "180")
(command "_insert" "blkuc9" "2880,919.98" "1" "1" "0")
(command "_insert" "blkuc9" "2880,919.61" "1" "1" "180")
(command "_insert" "blkuc9" "2880,920.35" "1" "1" "0")
(command "_insert" "blkuc9" "2880,919.98" "1" "1" "180")
(command "_insert" "blkuc9" "2880,920.72" "1" "1" "0")
(command "_insert" "blkuc9" "2880,920.35" "1" "1" "180")
(command "_insert" "blkuc9" "2880,921.09" "1" "1" "0")
(command "_insert" "blkuc9" "2880,920.72" "1" "1" "180")
(command "_insert" "blkuc9" "2880,921.46" "1" "1" "0")
(command "_insert" "blkuc9" "2880,921.09" "1" "1" "180")
(command "_insert" "blkuc9" "2880,921.83" "1" "1" "0")
(command "_insert" "blkuc9" "2880,921.46" "1" "1" "180")
(command "_insert" "blkuc9" "2880,922.2" "1" "1" "0")
(command "_insert" "blkuc9" "2880,921.83" "1" "1" "180")
(command "_insert" "blkuc9" "2880,922.57" "1" "1" "0")
(command "_insert" "blkuc9" "2880,922.2" "1" "1" "180")
(command "_insert" "blkuc9" "2880,922.94" "1" "1" "0")
(command "_insert" "blkuc9" "2880,922.57" "1" "1" "180")
(command "_insert" "blkuc9" "2880,923.31" "1" "1" "0")
(command "_insert" "blkuc9" "2880,922.94" "1" "1" "180")
(command "_insert" "blkuc9" "2880,923.68" "1" "1" "0")
(command "_insert" "blkuc9" "2880,923.31" "1" "1" "180")
(command "_insert" "blkuc9" "2880,924.05" "1" "1" "0")
(command "_insert" "blkuc9" "2880,923.68" "1" "1" "180")
(command "_insert" "blkuc9" "2880,924.42" "1" "1" "0")
(command "_insert" "blkuc9" "2880,924.05" "1" "1" "180")
(command "_insert" "blkuc9" "2880,924.79" "1" "1" "0")
(command "_insert" "blkuc9" "2880,924.42" "1" "1" "180")
(command "_insert" "blkuc9" "2880,925.16" "1" "1" "0")
(command "_insert" "blkuc9" "2880,924.79" "1" "1" "180")
(command "_insert" "blkuc9" "2880,925.53" "1" "1" "0")
(command "_insert" "blkuc9" "2880,925.16" "1" "1" "180")
(command "_insert" "blkuc9" "2880,925.9" "1" "1" "0")
(command "_insert" "blkuc9" "2880,925.53" "1" "1" "180")
(command "_insert" "blkuc9" "2880,926.27" "1" "1" "0")
(command "_insert" "blkuc9" "2880,925.9" "1" "1" "180")
(command "_insert" "blkuc9" "2880,926.64" "1" "1" "0")
(command "_insert" "blkuc9" "2880,926.27" "1" "1" "180")
(command "_insert" "blkuc9" "2880,927.01" "1" "1" "0")
(command "_insert" "blkuc9" "2880,926.64" "1" "1" "180")
(command "_insert" "blkuc9" "2880,927.38" "1" "1" "0")
(command "_insert" "blkuc9" "2880,927.01" "1" "1" "180")
(command "_insert" "blkuc9" "2880,927.75" "1" "1" "0")
(command "_insert" "blkuc9" "2880,927.38" "1" "1" "180")
(command "_layer" "set" "phccover" "")
(command "_rectangle" "2878.898,933.3" "2881.102,866.7")
(command "_layer" "set" "nitride" "")
(setq phc9 currobj)
(command "_layer" "set" "cover" "")
(command "_rectangle" "2878.898,836.7" "2881.102,963.3")
(command "_layer" "set" "nitride" "")
(command "_layer" "set" "text" "")
(command "_circle" "2877.948,846.7" "0.075")
(command "_circle" "2877.573,846.7" "0.15")
(command "_circle" "2877.198,846.7" "0.075")
(command "_circle" "2876.823,846.7" "0.15")
(command "_circle" "2877.948,848.7" "0.075")
(command "_circle" "2877.573,848.7" "0.075")
(command "_circle" "2877.198,848.7" "0.15")
(command "_circle" "2876.823,848.7" "0.15")
(command "_circle" "2877.948,850.7" "0.075")
(command "_circle" "2877.573,850.7" "0.15")
(command "_circle" "2877.198,850.7" "0.15")
(command "_circle" "2876.823,850.7" "0.15")
(command "_circle" "2877.948,852.7" "0.075")
(command "_circle" "2877.573,852.7" "0.075")
(command "_circle" "2877.198,852.7" "0.075")
(command "_circle" "2876.823,852.7" "0.075")
(command "_circle" "2876.448,852.7" "0.15")
(command "_circle" "2877.948,854.7" "0.075")
(command "_circle" "2877.573,854.7" "0.15")
(command "_circle" "2877.198,854.7" "0.075")
(command "_circle" "2876.823,854.7" "0.075")
(command "_circle" "2876.448,854.7" "0.15")
(command "_circle" "2877.948,856.7" "0.075")
(command "_circle" "2877.573,856.7" "0.075")
(command "_circle" "2877.198,856.7" "0.15")
(command "_circle" "2876.823,856.7" "0.075")
(command "_circle" "2876.448,856.7" "0.15")
(command "_circle" "2877.948,858.7" "0.075")
(command "_circle" "2877.573,858.7" "0.15")
(command "_circle" "2877.198,858.7" "0.15")
(command "_circle" "2876.823,858.7" "0.075")
(command "_circle" "2876.448,858.7" "0.15")
(command "_circle" "2877.948,860.7" "0.075")
(command "_circle" "2877.573,860.7" "0.075")
(command "_circle" "2877.198,860.7" "0.075")
(command "_circle" "2876.823,860.7" "0.15")
(command "_circle" "2876.448,860.7" "0.15")
(command "_circle" "2877.948,862.7" "0.075")
(command "_circle" "2877.573,862.7" "0.15")
(command "_circle" "2877.198,862.7" "0.075")
(command "_circle" "2876.823,862.7" "0.15")
(command "_circle" "2876.448,862.7" "0.15")
(command "_circle" "2877.948,864.7" "0.075")
(command "_circle" "2877.573,864.7" "0.075")
(command "_circle" "2877.198,864.7" "0.15")
(command "_circle" "2876.823,864.7" "0.15")
(command "_circle" "2876.448,864.7" "0.15")
(command "_circle" "2877.948,866.7" "0.075")
(command "_circle" "2877.573,866.7" "0.15")
(command "_circle" "2877.198,866.7" "0.15")
(command "_circle" "2876.823,866.7" "0.15")
(command "_circle" "2876.448,866.7" "0.15")
(command "_circle" "2877.948,868.7" "0.075")
(command "_circle" "2877.573,868.7" "0.075")
(command "_circle" "2877.198,868.7" "0.075")
(command "_circle" "2876.823,868.7" "0.075")
(command "_circle" "2876.448,868.7" "0.075")
(command "_circle" "2876.073,868.7" "0.15")
(command "_circle" "2877.948,870.7" "0.075")
(command "_circle" "2877.573,870.7" "0.15")
(command "_circle" "2877.198,870.7" "0.075")
(command "_circle" "2876.823,870.7" "0.075")
(command "_circle" "2876.448,870.7" "0.075")
(command "_circle" "2876.073,870.7" "0.15")
(command "_circle" "2877.948,872.7" "0.075")
(command "_circle" "2877.573,872.7" "0.075")
(command "_circle" "2877.198,872.7" "0.15")
(command "_circle" "2876.823,872.7" "0.075")
(command "_circle" "2876.448,872.7" "0.075")
(command "_circle" "2876.073,872.7" "0.15")
(command "_circle" "2877.948,874.7" "0.075")
(command "_circle" "2877.573,874.7" "0.15")
(command "_circle" "2877.198,874.7" "0.15")
(command "_circle" "2876.823,874.7" "0.075")
(command "_circle" "2876.448,874.7" "0.075")
(command "_circle" "2876.073,874.7" "0.15")
(command "_circle" "2877.948,876.7" "0.075")
(command "_circle" "2877.573,876.7" "0.075")
(command "_circle" "2877.198,876.7" "0.075")
(command "_circle" "2876.823,876.7" "0.15")
(command "_circle" "2876.448,876.7" "0.075")
(command "_circle" "2876.073,876.7" "0.15")
(command "_circle" "2877.948,878.7" "0.075")
(command "_circle" "2877.573,878.7" "0.15")
(command "_circle" "2877.198,878.7" "0.075")
(command "_circle" "2876.823,878.7" "0.15")
(command "_circle" "2876.448,878.7" "0.075")
(command "_circle" "2876.073,878.7" "0.15")
(command "_circle" "2877.948,880.7" "0.075")
(command "_circle" "2877.573,880.7" "0.075")
(command "_circle" "2877.198,880.7" "0.15")
(command "_circle" "2876.823,880.7" "0.15")
(command "_circle" "2876.448,880.7" "0.075")
(command "_circle" "2876.073,880.7" "0.15")
(command "_circle" "2877.948,882.7" "0.075")
(command "_circle" "2877.573,882.7" "0.15")
(command "_circle" "2877.198,882.7" "0.15")
(command "_circle" "2876.823,882.7" "0.15")
(command "_circle" "2876.448,882.7" "0.075")
(command "_circle" "2876.073,882.7" "0.15")
(command "_circle" "2877.948,884.7" "0.075")
(command "_circle" "2877.573,884.7" "0.075")
(command "_circle" "2877.198,884.7" "0.075")
(command "_circle" "2876.823,884.7" "0.075")
(command "_circle" "2876.448,884.7" "0.15")
(command "_circle" "2876.073,884.7" "0.15")
(command "_circle" "2877.948,886.7" "0.075")
(command "_circle" "2877.573,886.7" "0.15")
(command "_circle" "2877.198,886.7" "0.075")
(command "_circle" "2876.823,886.7" "0.075")
(command "_circle" "2876.448,886.7" "0.15")
(command "_circle" "2876.073,886.7" "0.15")
(command "_circle" "2877.948,888.7" "0.075")
(command "_circle" "2877.573,888.7" "0.075")
(command "_circle" "2877.198,888.7" "0.15")
(command "_circle" "2876.823,888.7" "0.075")
(command "_circle" "2876.448,888.7" "0.15")
(command "_circle" "2876.073,888.7" "0.15")
(command "_circle" "2877.948,890.7" "0.075")
(command "_circle" "2877.573,890.7" "0.15")
(command "_circle" "2877.198,890.7" "0.15")
(command "_circle" "2876.823,890.7" "0.075")
(command "_circle" "2876.448,890.7" "0.15")
(command "_circle" "2876.073,890.7" "0.15")
(command "_circle" "2877.948,892.7" "0.075")
(command "_circle" "2877.573,892.7" "0.075")
(command "_circle" "2877.198,892.7" "0.075")
(command "_circle" "2876.823,892.7" "0.15")
(command "_circle" "2876.448,892.7" "0.15")
(command "_circle" "2876.073,892.7" "0.15")
(command "_circle" "2877.948,894.7" "0.075")
(command "_circle" "2877.573,894.7" "0.15")
(command "_circle" "2877.198,894.7" "0.075")
(command "_circle" "2876.823,894.7" "0.15")
(command "_circle" "2876.448,894.7" "0.15")
(command "_circle" "2876.073,894.7" "0.15")
(command "_circle" "2877.948,896.7" "0.075")
(command "_circle" "2877.573,896.7" "0.075")
(command "_circle" "2877.198,896.7" "0.15")
(command "_circle" "2876.823,896.7" "0.15")
(command "_circle" "2876.448,896.7" "0.15")
(command "_circle" "2876.073,896.7" "0.15")
(command "_circle" "2877.948,898.7" "0.075")
(command "_circle" "2877.573,898.7" "0.15")
(command "_circle" "2877.198,898.7" "0.15")
(command "_circle" "2876.823,898.7" "0.15")
(command "_circle" "2876.448,898.7" "0.15")
(command "_circle" "2876.073,898.7" "0.15")
(command "_circle" "2877.948,900.7" "0.075")
(command "_circle" "2877.573,900.7" "0.075")
(command "_circle" "2877.198,900.7" "0.075")
(command "_circle" "2876.823,900.7" "0.075")
(command "_circle" "2876.448,900.7" "0.075")
(command "_circle" "2876.073,900.7" "0.075")
(command "_circle" "2875.698,900.7" "0.15")
(command "_circle" "2877.948,902.7" "0.075")
(command "_circle" "2877.573,902.7" "0.15")
(command "_circle" "2877.198,902.7" "0.075")
(command "_circle" "2876.823,902.7" "0.075")
(command "_circle" "2876.448,902.7" "0.075")
(command "_circle" "2876.073,902.7" "0.075")
(command "_circle" "2875.698,902.7" "0.15")
(command "_circle" "2877.948,904.7" "0.075")
(command "_circle" "2877.573,904.7" "0.075")
(command "_circle" "2877.198,904.7" "0.15")
(command "_circle" "2876.823,904.7" "0.075")
(command "_circle" "2876.448,904.7" "0.075")
(command "_circle" "2876.073,904.7" "0.075")
(command "_circle" "2875.698,904.7" "0.15")
(command "_circle" "2877.948,906.7" "0.075")
(command "_circle" "2877.573,906.7" "0.15")
(command "_circle" "2877.198,906.7" "0.15")
(command "_circle" "2876.823,906.7" "0.075")
(command "_circle" "2876.448,906.7" "0.075")
(command "_circle" "2876.073,906.7" "0.075")
(command "_circle" "2875.698,906.7" "0.15")
(command "_circle" "2877.948,908.7" "0.075")
(command "_circle" "2877.573,908.7" "0.075")
(command "_circle" "2877.198,908.7" "0.075")
(command "_circle" "2876.823,908.7" "0.15")
(command "_circle" "2876.448,908.7" "0.075")
(command "_circle" "2876.073,908.7" "0.075")
(command "_circle" "2875.698,908.7" "0.15")
(command "_circle" "2877.948,910.7" "0.075")
(command "_circle" "2877.573,910.7" "0.15")
(command "_circle" "2877.198,910.7" "0.075")
(command "_circle" "2876.823,910.7" "0.15")
(command "_circle" "2876.448,910.7" "0.075")
(command "_circle" "2876.073,910.7" "0.075")
(command "_circle" "2875.698,910.7" "0.15")
(command "_circle" "2877.948,912.7" "0.075")
(command "_circle" "2877.573,912.7" "0.075")
(command "_circle" "2877.198,912.7" "0.15")
(command "_circle" "2876.823,912.7" "0.15")
(command "_circle" "2876.448,912.7" "0.075")
(command "_circle" "2876.073,912.7" "0.075")
(command "_circle" "2875.698,912.7" "0.15")
(command "_circle" "2877.948,914.7" "0.075")
(command "_circle" "2877.573,914.7" "0.15")
(command "_circle" "2877.198,914.7" "0.15")
(command "_circle" "2876.823,914.7" "0.15")
(command "_circle" "2876.448,914.7" "0.075")
(command "_circle" "2876.073,914.7" "0.075")
(command "_circle" "2875.698,914.7" "0.15")
(command "_circle" "2877.948,916.7" "0.075")
(command "_circle" "2877.573,916.7" "0.075")
(command "_circle" "2877.198,916.7" "0.075")
(command "_circle" "2876.823,916.7" "0.075")
(command "_circle" "2876.448,916.7" "0.15")
(command "_circle" "2876.073,916.7" "0.075")
(command "_circle" "2875.698,916.7" "0.15")
(command "_circle" "2877.948,918.7" "0.075")
(command "_circle" "2877.573,918.7" "0.15")
(command "_circle" "2877.198,918.7" "0.075")
(command "_circle" "2876.823,918.7" "0.075")
(command "_circle" "2876.448,918.7" "0.15")
(command "_circle" "2876.073,918.7" "0.075")
(command "_circle" "2875.698,918.7" "0.15")
(command "_circle" "2877.948,920.7" "0.075")
(command "_circle" "2877.573,920.7" "0.075")
(command "_circle" "2877.198,920.7" "0.15")
(command "_circle" "2876.823,920.7" "0.075")
(command "_circle" "2876.448,920.7" "0.15")
(command "_circle" "2876.073,920.7" "0.075")
(command "_circle" "2875.698,920.7" "0.15")
(command "_circle" "2877.948,922.7" "0.075")
(command "_circle" "2877.573,922.7" "0.15")
(command "_circle" "2877.198,922.7" "0.15")
(command "_circle" "2876.823,922.7" "0.075")
(command "_circle" "2876.448,922.7" "0.15")
(command "_circle" "2876.073,922.7" "0.075")
(command "_circle" "2875.698,922.7" "0.15")
(command "_circle" "2877.948,924.7" "0.075")
(command "_circle" "2877.573,924.7" "0.075")
(command "_circle" "2877.198,924.7" "0.075")
(command "_circle" "2876.823,924.7" "0.15")
(command "_circle" "2876.448,924.7" "0.15")
(command "_circle" "2876.073,924.7" "0.075")
(command "_circle" "2875.698,924.7" "0.15")
(command "_circle" "2877.948,926.7" "0.075")
(command "_circle" "2877.573,926.7" "0.15")
(command "_circle" "2877.198,926.7" "0.075")
(command "_circle" "2876.823,926.7" "0.15")
(command "_circle" "2876.448,926.7" "0.15")
(command "_circle" "2876.073,926.7" "0.075")
(command "_circle" "2875.698,926.7" "0.15")
(command "_circle" "2877.948,928.7" "0.075")
(command "_circle" "2877.573,928.7" "0.075")
(command "_circle" "2877.198,928.7" "0.15")
(command "_circle" "2876.823,928.7" "0.15")
(command "_circle" "2876.448,928.7" "0.15")
(command "_circle" "2876.073,928.7" "0.075")
(command "_circle" "2875.698,928.7" "0.15")
(command "_circle" "2877.948,930.7" "0.075")
(command "_circle" "2877.573,930.7" "0.15")
(command "_circle" "2877.198,930.7" "0.15")
(command "_circle" "2876.823,930.7" "0.15")
(command "_circle" "2876.448,930.7" "0.15")
(command "_circle" "2876.073,930.7" "0.075")
(command "_circle" "2875.698,930.7" "0.15")
(command "_circle" "2877.948,932.7" "0.075")
(command "_circle" "2877.573,932.7" "0.075")
(command "_circle" "2877.198,932.7" "0.075")
(command "_circle" "2876.823,932.7" "0.075")
(command "_circle" "2876.448,932.7" "0.075")
(command "_circle" "2876.073,932.7" "0.15")
(command "_circle" "2875.698,932.7" "0.15")
(command "_circle" "2877.948,934.7" "0.075")
(command "_circle" "2877.573,934.7" "0.15")
(command "_circle" "2877.198,934.7" "0.075")
(command "_circle" "2876.823,934.7" "0.075")
(command "_circle" "2876.448,934.7" "0.075")
(command "_circle" "2876.073,934.7" "0.15")
(command "_circle" "2875.698,934.7" "0.15")
(command "_circle" "2877.948,936.7" "0.075")
(command "_circle" "2877.573,936.7" "0.075")
(command "_circle" "2877.198,936.7" "0.15")
(command "_circle" "2876.823,936.7" "0.075")
(command "_circle" "2876.448,936.7" "0.075")
(command "_circle" "2876.073,936.7" "0.15")
(command "_circle" "2875.698,936.7" "0.15")
(command "_circle" "2877.948,938.7" "0.075")
(command "_circle" "2877.573,938.7" "0.15")
(command "_circle" "2877.198,938.7" "0.15")
(command "_circle" "2876.823,938.7" "0.075")
(command "_circle" "2876.448,938.7" "0.075")
(command "_circle" "2876.073,938.7" "0.15")
(command "_circle" "2875.698,938.7" "0.15")
(command "_circle" "2877.948,940.7" "0.075")
(command "_circle" "2877.573,940.7" "0.075")
(command "_circle" "2877.198,940.7" "0.075")
(command "_circle" "2876.823,940.7" "0.15")
(command "_circle" "2876.448,940.7" "0.075")
(command "_circle" "2876.073,940.7" "0.15")
(command "_circle" "2875.698,940.7" "0.15")
(command "_circle" "2877.948,942.7" "0.075")
(command "_circle" "2877.573,942.7" "0.15")
(command "_circle" "2877.198,942.7" "0.075")
(command "_circle" "2876.823,942.7" "0.15")
(command "_circle" "2876.448,942.7" "0.075")
(command "_circle" "2876.073,942.7" "0.15")
(command "_circle" "2875.698,942.7" "0.15")
(command "_circle" "2877.948,944.7" "0.075")
(command "_circle" "2877.573,944.7" "0.075")
(command "_circle" "2877.198,944.7" "0.15")
(command "_circle" "2876.823,944.7" "0.15")
(command "_circle" "2876.448,944.7" "0.075")
(command "_circle" "2876.073,944.7" "0.15")
(command "_circle" "2875.698,944.7" "0.15")
(command "_circle" "2877.948,946.7" "0.075")
(command "_circle" "2877.573,946.7" "0.15")
(command "_circle" "2877.198,946.7" "0.15")
(command "_circle" "2876.823,946.7" "0.15")
(command "_circle" "2876.448,946.7" "0.075")
(command "_circle" "2876.073,946.7" "0.15")
(command "_circle" "2875.698,946.7" "0.15")
(command "_circle" "2877.948,948.7" "0.075")
(command "_circle" "2877.573,948.7" "0.075")
(command "_circle" "2877.198,948.7" "0.075")
(command "_circle" "2876.823,948.7" "0.075")
(command "_circle" "2876.448,948.7" "0.15")
(command "_circle" "2876.073,948.7" "0.15")
(command "_circle" "2875.698,948.7" "0.15")
(command "_circle" "2877.948,950.7" "0.075")
(command "_circle" "2877.573,950.7" "0.15")
(command "_circle" "2877.198,950.7" "0.075")
(command "_circle" "2876.823,950.7" "0.075")
(command "_circle" "2876.448,950.7" "0.15")
(command "_circle" "2876.073,950.7" "0.15")
(command "_circle" "2875.698,950.7" "0.15")
(command "_circle" "2877.948,952.7" "0.075")
(command "_circle" "2877.573,952.7" "0.075")
(command "_circle" "2877.198,952.7" "0.15")
(command "_circle" "2876.823,952.7" "0.075")
(command "_circle" "2876.448,952.7" "0.15")
(command "_circle" "2876.073,952.7" "0.15")
(command "_circle" "2875.698,952.7" "0.15")
(command "_circle" "2877.948,954.7" "0.075")
(command "_circle" "2877.573,954.7" "0.15")
(command "_circle" "2877.198,954.7" "0.15")
(command "_circle" "2876.823,954.7" "0.075")
(command "_circle" "2876.448,954.7" "0.15")
(command "_circle" "2876.073,954.7" "0.15")
(command "_circle" "2875.698,954.7" "0.15")
(command "_circle" "2877.948,956.7" "0.075")
(command "_circle" "2877.573,956.7" "0.075")
(command "_circle" "2877.198,956.7" "0.075")
(command "_circle" "2876.823,956.7" "0.15")
(command "_circle" "2876.448,956.7" "0.15")
(command "_circle" "2876.073,956.7" "0.15")
(command "_circle" "2875.698,956.7" "0.15")
(command "_circle" "2877.948,958.7" "0.075")
(command "_circle" "2877.573,958.7" "0.15")
(command "_circle" "2877.198,958.7" "0.075")
(command "_circle" "2876.823,958.7" "0.15")
(command "_circle" "2876.448,958.7" "0.15")
(command "_circle" "2876.073,958.7" "0.15")
(command "_circle" "2875.698,958.7" "0.15")
(command "_circle" "2877.948,960.7" "0.075")
(command "_circle" "2877.573,960.7" "0.075")
(command "_circle" "2877.198,960.7" "0.15")
(command "_circle" "2876.823,960.7" "0.15")
(command "_circle" "2876.448,960.7" "0.15")
(command "_circle" "2876.073,960.7" "0.15")
(command "_circle" "2875.698,960.7" "0.15")
(command "_circle" "2877.948,962.7" "0.075")
(command "_circle" "2877.573,962.7" "0.15")
(command "_circle" "2877.198,962.7" "0.15")
(command "_circle" "2876.823,962.7" "0.15")
(command "_circle" "2876.448,962.7" "0.15")
(command "_circle" "2876.073,962.7" "0.15")
(command "_circle" "2875.698,962.7" "0.15")
(command "_layer" "set" "nitride" "")
(command "_layer" "set" "text" "")
(command-s "_text" "2866.898,963.3" "2" "-90" "a = 370 nm" )
(sssetfirst nil (ssget "_L"))
(if (not (numberp (vl-string-search "Mac" (getvar "platform")))) (c:txtexp))
(command "_layer" "set" "nitride" "")
(command "_layer" "set" "text" "")
(command-s "_text" "2863.898,963.3" "2" "-90" "gap = 250 nm" )
(sssetfirst nil (ssget "_L"))
(if (not (numberp (vl-string-search "Mac" (getvar "platform")))) (c:txtexp))
(command "_layer" "set" "nitride" "")
(command "_layer" "set" "text" "")
(command-s "_text" "2860.898,963.3" "2" "-90" "amplitude = 127 nm" )
(sssetfirst nil (ssget "_L"))
(if (not (numberp (vl-string-search "Mac" (getvar "platform")))) (c:txtexp))
(command "_layer" "set" "nitride" "")
(command "_layer" "set" "text" "")
(command-s "_text" "2857.898,963.3" "2" "-90" "start width = 280 nm" )
(sssetfirst nil (ssget "_L"))
(if (not (numberp (vl-string-search "Mac" (getvar "platform")))) (c:txtexp))
(command "_layer" "set" "nitride" "")
(command "_layer" "set" "text" "")
(command-s "_text" "2854.898,963.3" "2" "-90" "width = 299 nm" )
(sssetfirst nil (ssget "_L"))
(if (not (numberp (vl-string-search "Mac" (getvar "platform")))) (c:txtexp))
(command "_layer" "set" "nitride" "")
(command "_layer" "set" "text" "")
(command-s "_text" "2851.898,963.3" "2" "-90" "taper: 15" )
(sssetfirst nil (ssget "_L"))
(if (not (numberp (vl-string-search "Mac" (getvar "platform")))) (c:txtexp))
(command "_layer" "set" "nitride" "")
(command "_layer" "set" "text" "")
(command-s "_text" "2848.898,963.3" "2" "-90" "nominal: 150" )
(sssetfirst nil (ssget "_L"))
(if (not (numberp (vl-string-search "Mac" (getvar "platform")))) (c:txtexp))
(command "_layer" "set" "nitride" "")
(command "_layer" "set" "indicators" "")
(setq coords (list 
(list 2800.415 940) 
(list 2800.415 920) 
(list 2780.415 900) 
(list 2800.415 880) 
(list 2800.415 860) 
(list 2800.415 900) 
(list 2800.415 887.0711) 
(list 2787.4861 900) 
(list 2800.415 912.9289) 
(list 2800.415 900)))
(apply 'command (append '("pline") coords '("c")))
(command "._fillet" "radius" "1" "._fillet" "P" (entlast))
(setq coords (list 
(list 2959.585 940) 
(list 2959.585 920) 
(list 2979.585 900) 
(list 2959.585 880) 
(list 2959.585 860) 
(list 2959.585 900) 
(list 2959.585 887.0711) 
(list 2972.5139 900) 
(list 2959.585 912.9289) 
(list 2959.585 900)))
(apply 'command (append '("pline") coords '("c")))
(command "._fillet" "radius" "1" "._fillet" "P" (entlast))
(command "_layer" "set" "holes" "")
(command "_circle" "2798.0629,914.1124" "0.5")
(command "_circle" "2795.7109,911.7603" "0.5")
(command "_circle" "2793.3588,909.4083" "0.5")
(command "_circle" "2791.0067,907.0562" "0.5")
(command "_circle" "2788.6547,904.7041" "0.5")
(command "_circle" "2786.3026,902.3521" "0.5")
(command "_circle" "2783.9505,900" "0.5")
(command "_circle" "2786.3026,897.6479" "0.5")
(command "_circle" "2788.6547,895.2959" "0.5")
(command "_circle" "2791.0067,892.9438" "0.5")
(command "_circle" "2793.3588,890.5917" "0.5")
(command "_circle" "2795.7109,888.2397" "0.5")
(command "_circle" "2798.0629,885.8876" "0.5")
(command "_circle" "2961.9371,914.1124" "0.5")
(command "_circle" "2964.2891,911.7603" "0.5")
(command "_circle" "2966.6412,909.4083" "0.5")
(command "_circle" "2968.9933,907.0562" "0.5")
(command "_circle" "2971.3453,904.7041" "0.5")
(command "_circle" "2973.6974,902.3521" "0.5")
(command "_circle" "2976.0495,900" "0.5")
(command "_circle" "2973.6974,897.6479" "0.5")
(command "_circle" "2971.3453,895.2959" "0.5")
(command "_circle" "2968.9933,892.9438" "0.5")
(command "_circle" "2966.6412,890.5917" "0.5")
(command "_circle" "2964.2891,888.2397" "0.5")
(command "_circle" "2961.9371,885.8876" "0.5")
(command "_layer" "set" "nitride" "")
(command "_block" "blkcoupler9" "2880,900" coupler9 "")
(command "_insert" "blkcoupler9" "2880,900" "1" "1" "0")
(command "_insert" "blkcoupler9" "2880,900" "1" "1" "180")
(command "_block" "blksinglenanobeam9" "2880,900" singlenanobeam9 "")
(command "_insert" "blksinglenanobeam9" "2880,900" "1" "1" "0")
(command "_insert" "blksinglenanobeam9" "2880,900" "1" "1" "180")
(command "_block" "blkanglednodearray9" "2880,900" anglednodearray9 "")
(command "_insert" "blkanglednodearray9" "2880,900" "1" "1" "0")
(command "_insert" "blkanglednodearray9" "2880,900" "1" "1" "180")
(command "_block" "blkcooledsinglenanobeam9" "2880,900" cooledsinglenanobeam9 "")
(command "_insert" "blkcooledsinglenanobeam9" "2880,900" "1" "1" "0")
(command "_insert" "blkcooledsinglenanobeam9" "2880,900" "1" "1" "180")
(command "_block" "blkyjunction9" "2880,900" yjunction9 "")
(command "_insert" "blkyjunction9" "2880,900" "1" "1" "0")
(command "_insert" "blkyjunction9" "2880,900" "1" "1" "180")
; DRAWING BULGING VEE GROOVE
(command "_layer" "set" "vgroove" "")
(setq coords (list 
(list 2805.415 -605) 
(list 2805.415 0) 
(list 2805.415 0) 
(list 2805.415 1800) 
(list 2805.415 1800) 
(list 2805.415 2405) 
(list 2954.585 2405) 
(list 2954.585 1800) 
(list 2954.585 1800) 
(list 2954.585 0) 
(list 2954.585 0) 
(list 2954.585 -605)))
(apply 'command (append '("pline") coords '("c")))
(command "._fillet" "radius" "0" "._fillet" "P" (entlast))
(command "_layer" "set" "window" "")
(command "_rectangle" "2805.415,-1935" "2954.585,-600")
(command "_rectangle" "2805.415,2400" "2954.585,5300")
(command "_layer" "set" "grid" "")
(command "_rectangle" "2806.415,-1934" "2829.9433,-1909.2133")
(command "_array" "last" "" "R" "75" "3" "25.7867" "24.5283")
(command "_rectangle" "2881,-1934" "2904.5283,-1909.2133")
(command "_array" "last" "" "R" "75" "3" "25.7867" "24.5283")
(command "_rectangle" "2806.415,1" "2829.9433,25.7")
(command "_array" "last" "" "R" "70" "3" "25.7" "24.5283")
(command "_rectangle" "2881,1" "2904.5283,25.7")
(command "_array" "last" "" "R" "70" "3" "25.7" "24.5283")
(command "_rectangle" "2806.415,1801" "2829.9433,1825.9185")
(command "_array" "last" "" "R" "135" "3" "25.9185" "24.5283")
(command "_rectangle" "2881,1801" "2904.5283,1825.9185")
(command "_array" "last" "" "R" "135" "3" "25.9185" "24.5283")
(command "_layer" "set" "vgrooveFDA" "")
(command "_rectangle" "2954.585,-2233" "2805.415,-1933")
(command "_layer" "set" "nitride" "")
(command "_layer" "set" "holes" "")
(command "_circle" "2957.085,331.5" "0.5")
(command "_array" "last" "" "R" "379" "1" "3" "2.5")
(command "_circle" "2802.915,331.5" "0.5")
(command "_array" "last" "" "R" "379" "1" "3" "-2.5")
(command "_layer" "set" "nitride" "")
(command "_layer" "set" "window" "")
(command "_layer" "set" "window" "")
(command "_rectangle" "2959.585,0" "3120.415,1800")
(command "._fillet" "radius" "20" "._fillet" "P" (entlast))
(command "_layer" "set" "grid" "")
(command "_rectangle" "2960.585,1" "2982.4179,25.7")
(command "_array" "last" "" "R" "70" "7" "25.7" "22.8329")
(command "_layer" "set" "nitride" "")
; DRAWING REGION LAYER
(command "_layer" "set" "regionLayer9" "")
(command "_rectangle" "2800,-460" "2960,2260")
(command "_layer" "set" "nitride" "")
(setq coupler9 nil)
(setq singlenanobeam9 nil)
(setq anglednodearray9 nil)
(setq cooledsinglenanobeam9 nil)
(setq yjunction9 nil)
; DEVICE #10
(command "_layer" "set" "window" "")
(command "_circle" "3112.915,-415" "5")
(command "_circle" "3112.915,-402.5" "5")
(command "_circle" "3112.915,-390" "5")
(command "_circle" "3112.915,-377.5" "5")
(command "_circle" "3100.415,-415" "5")
(command "_circle" "3100.415,-402.5" "5")
(command "_circle" "3100.415,-390" "5")
(command "_circle" "3100.415,-377.5" "5")
(command "_circle" "3087.915,-415" "5")
(command "_circle" "3087.915,-402.5" "5")
(command "_layer" "set" "nitride" "")
(setq currobj nil)
(setq currobj (ssadd))
; DRAWING COUPLER
(setq coords (list 
(list 3200.0635 -415) 
(list 3200.0635 -413) 
(list 3273.585 -413) 
(list 3273.585 -413) 
(list 3273.9677 -413.0761) 
(list 3274.2921 -413.2929) 
(list 3274.5089 -413.6173) 
(list 3274.585 -414) 
(list 3274.585 -411.8) 
(list 3274.585 -411.8) 
(list 3274.5089 -412.1827) 
(list 3274.2921 -412.5071) 
(list 3273.9677 -412.7239) 
(list 3273.585 -412.8) 
(list 3200.0635 -412.8) 
(list 3200.0635 -410.8) 
(list 3199.9365 -410.8) 
(list 3199.9365 -412.8) 
(list 3126.415 -412.8) 
(list 3126.0323 -412.7239) 
(list 3125.7079 -412.5071) 
(list 3125.4911 -412.1827) 
(list 3125.415 -411.8) 
(list 3125.415 -411.8) 
(list 3125.415 -414) 
(list 3125.4911 -413.6173) 
(list 3125.7079 -413.2929) 
(list 3126.0323 -413.0761) 
(list 3126.415 -413) 
(list 3126.415 -413) 
(list 3199.9365 -413) 
(list 3199.9365 -415)))
(apply 'command (append '("pline") coords '("c")))
(setq currobj (ssadd (entlast) currobj))
(command "._fillet" "radius" "0.3" "._fillet" "P" (entlast))
(command "_layer" "set" "holes" "")
(command "_circle" "3200,-412.9" "0.113")
(setq currobj (ssadd (entlast) currobj))
(command "_layer" "set" "nitride" "")
(command "_layer" "set" "text" "")
(command "_circle" "3199.2,-415" "0.075")
(command "_circle" "3199.2,-414.7" "0.075")
(command "_circle" "3199.2,-414.4" "0.075")
(command "_circle" "3198.9,-415" "0.075")
(command "_circle" "3198.9,-414.7" "0.075")
(command "_circle" "3198.9,-414.4" "0.075")
(command "_circle" "3198.6,-415" "0.075")
(command "_circle" "3198.6,-414.7" "0.075")
(command "_circle" "3198.6,-414.4" "0.075")
(command "_layer" "set" "nitride" "")
(command "_layer" "set" "prebias" "")
(command "_rectangle" "3125.415,-414" "3274.585,-411.8")
(setq currobj (ssadd (entlast) currobj))
(command "_rectangle" "3199.9365,-415" "3200.0635,-410.8")
(setq currobj (ssadd (entlast) currobj))
(command "_layer" "set" "nitride" "")
(setq coupler10 currobj)
(setq currobj nil)
(setq currobj (ssadd))
; DRAWING SINGLE NANOBEAM
(setq coords (list 
(list 3200.0635 -410.8) 
(list 3200.0635 -409.1417) 
(list 3200.0635 -407.4833) 
(list 3200.0635 -405.825) 
(list 3200.0635 -404.1667) 
(list 3200.0635 -402.5083) 
(list 3200.0635 -400.85) 
(list 3200.0635 -399.1917) 
(list 3200.0635 -397.5333) 
(list 3200.0636 -395.875) 
(list 3200.0636 -394.2167) 
(list 3200.0636 -392.5583) 
(list 3200.0636 -390.9) 
(list 3200.0637 -389.2417) 
(list 3200.0637 -387.5833) 
(list 3200.0637 -385.925) 
(list 3200.0638 -384.2667) 
(list 3200.0638 -382.6083) 
(list 3200.0639 -380.95) 
(list 3200.064 -379.2917) 
(list 3200.0641 -377.6333) 
(list 3200.0642 -375.975) 
(list 3200.0642 -374.3167) 
(list 3200.0644 -372.6583) 
(list 3200.0645 -371) 
(list 3200.0646 -369.3417) 
(list 3200.0647 -367.6833) 
(list 3200.0649 -366.025) 
(list 3200.065 -364.3667) 
(list 3200.0652 -362.7083) 
(list 3200.0654 -361.05) 
(list 3200.0656 -359.3917) 
(list 3200.0658 -357.7333) 
(list 3200.066 -356.075) 
(list 3200.0663 -354.4167) 
(list 3200.0665 -352.7583) 
(list 3200.0668 -351.1) 
(list 3200.0671 -349.4417) 
(list 3200.0674 -347.7833) 
(list 3200.0677 -346.125) 
(list 3200.068 -344.4667) 
(list 3200.0683 -342.8083) 
(list 3200.0687 -341.15) 
(list 3200.0691 -339.4917) 
(list 3200.0695 -337.8333) 
(list 3200.0699 -336.175) 
(list 3200.0703 -334.5167) 
(list 3200.0708 -332.8583) 
(list 3200.0713 -331.2) 
(list 3200.0718 -329.5417) 
(list 3200.0723 -327.8833) 
(list 3200.0728 -326.225) 
(list 3200.0734 -324.5667) 
(list 3200.074 -322.9083) 
(list 3200.0746 -321.25) 
(list 3200.0752 -319.5917) 
(list 3200.0758 -317.9333) 
(list 3200.0765 -316.275) 
(list 3200.0772 -314.6167) 
(list 3200.0779 -312.9583) 
(list 3200.0787 -311.3) 
(list 3200.0795 -309.6417) 
(list 3200.0803 -307.9833) 
(list 3200.0811 -306.325) 
(list 3200.0819 -304.6667) 
(list 3200.0828 -303.0083) 
(list 3200.0837 -301.35) 
(list 3200.0846 -299.6917) 
(list 3200.0856 -298.0333) 
(list 3200.0866 -296.375) 
(list 3200.0876 -294.7167) 
(list 3200.0887 -293.0583) 
(list 3200.0897 -291.4) 
(list 3200.0909 -289.7417) 
(list 3200.092 -288.0833) 
(list 3200.0932 -286.425) 
(list 3200.0944 -284.7667) 
(list 3200.0956 -283.1083) 
(list 3200.0969 -281.45) 
(list 3200.0982 -279.7917) 
(list 3200.0995 -278.1333) 
(list 3200.1009 -276.475) 
(list 3200.1023 -274.8167) 
(list 3200.1037 -273.1583) 
(list 3200.1052 -271.5) 
(list 3200.1067 -269.8417) 
(list 3200.1082 -268.1833) 
(list 3200.1098 -266.525) 
(list 3200.1114 -264.8667) 
(list 3200.1131 -263.2083) 
(list 3200.1148 -261.55) 
(list 3200.1165 -259.8917) 
(list 3200.1183 -258.2333) 
(list 3200.1201 -256.575) 
(list 3200.1219 -254.9167) 
(list 3200.1238 -253.2583) 
(list 3200.1257 -251.6) 
(list 3200.1277 -249.9417) 
(list 3200.1297 -248.2833) 
(list 3200.1317 -246.625) 
(list 3200.1338 -244.9667) 
(list 3200.1359 -243.3083) 
(list 3200.1381 -241.65) 
(list 3200.1403 -239.9917) 
(list 3200.1426 -238.3333) 
(list 3200.1449 -236.675) 
(list 3200.1472 -235.0167) 
(list 3200.1496 -233.3583) 
(list 3200.1521 -231.7) 
(list 3200.1546 -230.0417) 
(list 3200.1571 -228.3833) 
(list 3200.1597 -226.725) 
(list 3200.1623 -225.0667) 
(list 3200.165 -223.4083) 
(list 3200.1677 -221.75) 
(list 3200.1704 -220.0917) 
(list 3200.1733 -218.4333) 
(list 3200.1761 -216.775) 
(list 3200.179 -215.1167) 
(list 3200.182 -213.4583) 
(list 3200.185 -211.8) 
(list 3199.815 -211.8) 
(list 3199.818 -213.4583) 
(list 3199.821 -215.1167) 
(list 3199.8239 -216.775) 
(list 3199.8268 -218.4333) 
(list 3199.8296 -220.0917) 
(list 3199.8323 -221.75) 
(list 3199.835 -223.4083) 
(list 3199.8377 -225.0667) 
(list 3199.8403 -226.725) 
(list 3199.8429 -228.3833) 
(list 3199.8454 -230.0417) 
(list 3199.8479 -231.7) 
(list 3199.8504 -233.3583) 
(list 3199.8528 -235.0167) 
(list 3199.8551 -236.675) 
(list 3199.8574 -238.3333) 
(list 3199.8597 -239.9917) 
(list 3199.8619 -241.65) 
(list 3199.8641 -243.3083) 
(list 3199.8662 -244.9667) 
(list 3199.8683 -246.625) 
(list 3199.8703 -248.2833) 
(list 3199.8723 -249.9417) 
(list 3199.8743 -251.6) 
(list 3199.8762 -253.2583) 
(list 3199.8781 -254.9167) 
(list 3199.8799 -256.575) 
(list 3199.8817 -258.2333) 
(list 3199.8835 -259.8917) 
(list 3199.8852 -261.55) 
(list 3199.8869 -263.2083) 
(list 3199.8886 -264.8667) 
(list 3199.8902 -266.525) 
(list 3199.8918 -268.1833) 
(list 3199.8933 -269.8417) 
(list 3199.8948 -271.5) 
(list 3199.8963 -273.1583) 
(list 3199.8977 -274.8167) 
(list 3199.8991 -276.475) 
(list 3199.9005 -278.1333) 
(list 3199.9018 -279.7917) 
(list 3199.9031 -281.45) 
(list 3199.9044 -283.1083) 
(list 3199.9056 -284.7667) 
(list 3199.9068 -286.425) 
(list 3199.908 -288.0833) 
(list 3199.9091 -289.7417) 
(list 3199.9103 -291.4) 
(list 3199.9113 -293.0583) 
(list 3199.9124 -294.7167) 
(list 3199.9134 -296.375) 
(list 3199.9144 -298.0333) 
(list 3199.9154 -299.6917) 
(list 3199.9163 -301.35) 
(list 3199.9172 -303.0083) 
(list 3199.9181 -304.6667) 
(list 3199.9189 -306.325) 
(list 3199.9197 -307.9833) 
(list 3199.9205 -309.6417) 
(list 3199.9213 -311.3) 
(list 3199.9221 -312.9583) 
(list 3199.9228 -314.6167) 
(list 3199.9235 -316.275) 
(list 3199.9242 -317.9333) 
(list 3199.9248 -319.5917) 
(list 3199.9254 -321.25) 
(list 3199.926 -322.9083) 
(list 3199.9266 -324.5667) 
(list 3199.9272 -326.225) 
(list 3199.9277 -327.8833) 
(list 3199.9282 -329.5417) 
(list 3199.9287 -331.2) 
(list 3199.9292 -332.8583) 
(list 3199.9297 -334.5167) 
(list 3199.9301 -336.175) 
(list 3199.9305 -337.8333) 
(list 3199.9309 -339.4917) 
(list 3199.9313 -341.15) 
(list 3199.9317 -342.8083) 
(list 3199.932 -344.4667) 
(list 3199.9323 -346.125) 
(list 3199.9326 -347.7833) 
(list 3199.9329 -349.4417) 
(list 3199.9332 -351.1) 
(list 3199.9335 -352.7583) 
(list 3199.9337 -354.4167) 
(list 3199.934 -356.075) 
(list 3199.9342 -357.7333) 
(list 3199.9344 -359.3917) 
(list 3199.9346 -361.05) 
(list 3199.9348 -362.7083) 
(list 3199.935 -364.3667) 
(list 3199.9351 -366.025) 
(list 3199.9353 -367.6833) 
(list 3199.9354 -369.3417) 
(list 3199.9355 -371) 
(list 3199.9356 -372.6583) 
(list 3199.9358 -374.3167) 
(list 3199.9358 -375.975) 
(list 3199.9359 -377.6333) 
(list 3199.936 -379.2917) 
(list 3199.9361 -380.95) 
(list 3199.9362 -382.6083) 
(list 3199.9362 -384.2667) 
(list 3199.9363 -385.925) 
(list 3199.9363 -387.5833) 
(list 3199.9363 -389.2417) 
(list 3199.9364 -390.9) 
(list 3199.9364 -392.5583) 
(list 3199.9364 -394.2167) 
(list 3199.9364 -395.875) 
(list 3199.9365 -397.5333) 
(list 3199.9365 -399.1917) 
(list 3199.9365 -400.85) 
(list 3199.9365 -402.5083) 
(list 3199.9365 -404.1667) 
(list 3199.9365 -405.825) 
(list 3199.9365 -407.4833) 
(list 3199.9365 -409.1417) 
(list 3199.9365 -410.8)))
(apply 'command (append '("pline") coords '("c")))
(setq currobj (ssadd (entlast) currobj))
(command "_layer" "set" "prebias" "")
(command "_rectangle" "3199.815,-410.8" "3200.185,-211.8")
(setq currobj (ssadd (entlast) currobj))
(command "_layer" "set" "nitride" "")
(setq singlenanobeam10 currobj)
(setq currobj nil)
(setq currobj (ssadd))
; DRAWING NODE ARRAY
(setq coords (list 
(list 3200.185 -211.8) 
(list 3200.5625 -201.8) 
(list 3200.5625 -201.8) 
(list 3200.5625 -200.8) 
(list 3274.585 -212.6864) 
(list 3274.585 -207.7434) 
(list 3200.5625 -197.357) 
(list 3200.5625 -196.357) 
(list 3200.5625 -196.357) 
(list 3200.2625 -186.357) 
(list 3199.7375 -186.357) 
(list 3199.4375 -196.357) 
(list 3199.4375 -196.357) 
(list 3199.4375 -197.357) 
(list 3125.415 -207.7434) 
(list 3125.415 -212.6864) 
(list 3199.4375 -200.8) 
(list 3199.4375 -201.8) 
(list 3199.4375 -201.8) 
(list 3199.815 -211.8)))
(apply 'command (append '("pline") coords '("c")))
(setq currobj (ssadd (entlast) currobj))
(command "_layer" "set" "prebias" "")
(setq coords (list 
(list 3199.4375 -212.6864) 
(list 3199.4375 -200.8) 
(list 3125.415 -212.6864) 
(list 3125.415 -207.7434) 
(list 3199.4375 -197.357) 
(list 3199.4375 -186.357) 
(list 3200.5625 -186.357) 
(list 3200.5625 -197.357) 
(list 3274.585 -207.7434) 
(list 3274.585 -212.6864) 
(list 3200.5625 -200.8) 
(list 3200.5625 -212.6864)))
(apply 'command (append '("pline") coords '("c")))
(setq currobj (ssadd (entlast) currobj))
(command "_layer" "set" "nitride" "")
(command "_layer" "set" "fda1" "")
(setq coords (list 
(list 3200.5625 -200.657) 
(list 3274.585 -212.5434) 
(list 3274.585 -212.3664) 
(list 3200.5625 -200.58)))
(apply 'command (append '("pline") coords '("c")))
(setq currobj (ssadd (entlast) currobj))
(setq coords (list 
(list 3200.5625 -200.437) 
(list 3274.585 -212.2234) 
(list 3274.585 -212.0464) 
(list 3200.5625 -200.36)))
(apply 'command (append '("pline") coords '("c")))
(setq currobj (ssadd (entlast) currobj))
(setq coords (list 
(list 3200.5625 -200.217) 
(list 3274.585 -211.9034) 
(list 3274.585 -211.7264) 
(list 3200.5625 -200.14)))
(apply 'command (append '("pline") coords '("c")))
(setq currobj (ssadd (entlast) currobj))
(setq coords (list 
(list 3200.5625 -199.997) 
(list 3274.585 -211.5834) 
(list 3274.585 -211.4064) 
(list 3200.5625 -199.92)))
(apply 'command (append '("pline") coords '("c")))
(setq currobj (ssadd (entlast) currobj))
(setq coords (list 
(list 3200.5625 -199.777) 
(list 3274.585 -211.2634) 
(list 3274.585 -211.0864) 
(list 3200.5625 -199.7)))
(apply 'command (append '("pline") coords '("c")))
(setq currobj (ssadd (entlast) currobj))
(setq coords (list 
(list 3200.5625 -199.557) 
(list 3274.585 -210.9434) 
(list 3274.585 -210.7664) 
(list 3200.5625 -199.48)))
(apply 'command (append '("pline") coords '("c")))
(setq currobj (ssadd (entlast) currobj))
(setq coords (list 
(list 3200.5625 -199.337) 
(list 3274.585 -210.6234) 
(list 3274.585 -210.4464) 
(list 3200.5625 -199.26)))
(apply 'command (append '("pline") coords '("c")))
(setq currobj (ssadd (entlast) currobj))
(setq coords (list 
(list 3200.5625 -199.117) 
(list 3274.585 -210.3034) 
(list 3274.585 -210.1264) 
(list 3200.5625 -199.04)))
(apply 'command (append '("pline") coords '("c")))
(setq currobj (ssadd (entlast) currobj))
(setq coords (list 
(list 3200.5625 -198.897) 
(list 3274.585 -209.9834) 
(list 3274.585 -209.8064) 
(list 3200.5625 -198.82)))
(apply 'command (append '("pline") coords '("c")))
(setq currobj (ssadd (entlast) currobj))
(setq coords (list 
(list 3200.5625 -198.677) 
(list 3274.585 -209.6634) 
(list 3274.585 -209.4864) 
(list 3200.5625 -198.6)))
(apply 'command (append '("pline") coords '("c")))
(setq currobj (ssadd (entlast) currobj))
(setq coords (list 
(list 3200.5625 -198.457) 
(list 3274.585 -209.3434) 
(list 3274.585 -209.1664) 
(list 3200.5625 -198.38)))
(apply 'command (append '("pline") coords '("c")))
(setq currobj (ssadd (entlast) currobj))
(setq coords (list 
(list 3200.5625 -198.237) 
(list 3274.585 -209.0234) 
(list 3274.585 -208.8464) 
(list 3200.5625 -198.16)))
(apply 'command (append '("pline") coords '("c")))
(setq currobj (ssadd (entlast) currobj))
(setq coords (list 
(list 3200.5625 -198.017) 
(list 3274.585 -208.7034) 
(list 3274.585 -208.5264) 
(list 3200.5625 -197.94)))
(apply 'command (append '("pline") coords '("c")))
(setq currobj (ssadd (entlast) currobj))
(setq coords (list 
(list 3200.5625 -197.797) 
(list 3274.585 -208.3834) 
(list 3274.585 -208.2064) 
(list 3200.5625 -197.72)))
(apply 'command (append '("pline") coords '("c")))
(setq currobj (ssadd (entlast) currobj))
(setq coords (list 
(list 3200.5625 -197.577) 
(list 3274.585 -208.0634) 
(list 3274.585 -207.8864) 
(list 3200.5625 -197.5)))
(apply 'command (append '("pline") coords '("c")))
(setq currobj (ssadd (entlast) currobj))
(setq coords (list 
(list 3199.4375 -197.5) 
(list 3125.415 -207.8864) 
(list 3125.415 -208.0634) 
(list 3199.4375 -197.577)))
(apply 'command (append '("pline") coords '("c")))
(setq currobj (ssadd (entlast) currobj))
(setq coords (list 
(list 3199.4375 -197.72) 
(list 3125.415 -208.2064) 
(list 3125.415 -208.3834) 
(list 3199.4375 -197.797)))
(apply 'command (append '("pline") coords '("c")))
(setq currobj (ssadd (entlast) currobj))
(setq coords (list 
(list 3199.4375 -197.94) 
(list 3125.415 -208.5264) 
(list 3125.415 -208.7034) 
(list 3199.4375 -198.017)))
(apply 'command (append '("pline") coords '("c")))
(setq currobj (ssadd (entlast) currobj))
(setq coords (list 
(list 3199.4375 -198.16) 
(list 3125.415 -208.8464) 
(list 3125.415 -209.0234) 
(list 3199.4375 -198.237)))
(apply 'command (append '("pline") coords '("c")))
(setq currobj (ssadd (entlast) currobj))
(setq coords (list 
(list 3199.4375 -198.38) 
(list 3125.415 -209.1664) 
(list 3125.415 -209.3434) 
(list 3199.4375 -198.457)))
(apply 'command (append '("pline") coords '("c")))
(setq currobj (ssadd (entlast) currobj))
(setq coords (list 
(list 3199.4375 -198.6) 
(list 3125.415 -209.4864) 
(list 3125.415 -209.6634) 
(list 3199.4375 -198.677)))
(apply 'command (append '("pline") coords '("c")))
(setq currobj (ssadd (entlast) currobj))
(setq coords (list 
(list 3199.4375 -198.82) 
(list 3125.415 -209.8064) 
(list 3125.415 -209.9834) 
(list 3199.4375 -198.897)))
(apply 'command (append '("pline") coords '("c")))
(setq currobj (ssadd (entlast) currobj))
(setq coords (list 
(list 3199.4375 -199.04) 
(list 3125.415 -210.1264) 
(list 3125.415 -210.3034) 
(list 3199.4375 -199.117)))
(apply 'command (append '("pline") coords '("c")))
(setq currobj (ssadd (entlast) currobj))
(setq coords (list 
(list 3199.4375 -199.26) 
(list 3125.415 -210.4464) 
(list 3125.415 -210.6234) 
(list 3199.4375 -199.337)))
(apply 'command (append '("pline") coords '("c")))
(setq currobj (ssadd (entlast) currobj))
(setq coords (list 
(list 3199.4375 -199.48) 
(list 3125.415 -210.7664) 
(list 3125.415 -210.9434) 
(list 3199.4375 -199.557)))
(apply 'command (append '("pline") coords '("c")))
(setq currobj (ssadd (entlast) currobj))
(setq coords (list 
(list 3199.4375 -199.7) 
(list 3125.415 -211.0864) 
(list 3125.415 -211.2634) 
(list 3199.4375 -199.777)))
(apply 'command (append '("pline") coords '("c")))
(setq currobj (ssadd (entlast) currobj))
(setq coords (list 
(list 3199.4375 -199.92) 
(list 3125.415 -211.4064) 
(list 3125.415 -211.5834) 
(list 3199.4375 -199.997)))
(apply 'command (append '("pline") coords '("c")))
(setq currobj (ssadd (entlast) currobj))
(setq coords (list 
(list 3199.4375 -200.14) 
(list 3125.415 -211.7264) 
(list 3125.415 -211.9034) 
(list 3199.4375 -200.217)))
(apply 'command (append '("pline") coords '("c")))
(setq currobj (ssadd (entlast) currobj))
(setq coords (list 
(list 3199.4375 -200.36) 
(list 3125.415 -212.0464) 
(list 3125.415 -212.2234) 
(list 3199.4375 -200.437)))
(apply 'command (append '("pline") coords '("c")))
(setq currobj (ssadd (entlast) currobj))
(setq coords (list 
(list 3199.4375 -200.58) 
(list 3125.415 -212.3664) 
(list 3125.415 -212.5434) 
(list 3199.4375 -200.657)))
(apply 'command (append '("pline") coords '("c")))
(setq currobj (ssadd (entlast) currobj))
(command "_layer" "set" "nitride" "")
(command "_layer" "set" "text" "")
(command "_circle" "3198.985,-211.8" "0.075")
(command "_circle" "3198.985,-211.5" "0.075")
(command "_circle" "3198.985,-211.2" "0.075")
(command "_circle" "3198.985,-210.9" "0.075")
(command "_circle" "3198.985,-210.6" "0.075")
(command "_circle" "3198.685,-211.8" "0.075")
(command "_circle" "3198.685,-211.5" "0.075")
(command "_circle" "3198.685,-211.2" "0.075")
(command "_circle" "3198.685,-210.9" "0.075")
(command "_circle" "3198.685,-210.6" "0.075")
(command "_circle" "3198.385,-211.8" "0.075")
(command "_circle" "3198.385,-211.5" "0.075")
(command "_circle" "3198.385,-211.2" "0.075")
(command "_circle" "3198.385,-210.9" "0.075")
(command "_circle" "3198.385,-210.6" "0.075")
(command "_circle" "3198.085,-211.8" "0.075")
(command "_circle" "3198.085,-211.5" "0.075")
(command "_circle" "3198.085,-211.2" "0.075")
(command "_circle" "3198.085,-210.9" "0.075")
(command "_circle" "3198.085,-210.6" "0.075")
(command "_circle" "3197.785,-211.8" "0.075")
(command "_circle" "3197.785,-211.5" "0.075")
(command "_circle" "3197.785,-211.2" "0.075")
(command "_circle" "3197.785,-210.9" "0.075")
(command "_circle" "3197.785,-210.6" "0.075")
(command "_layer" "set" "nitride" "")
(setq anglednodearray10 currobj)
(setq currobj nil)
(setq currobj (ssadd))
; DRAWING COOLED SINGLE NANOBEAM
(setq coords (list 
(list 3200.2625 -186.357) 
(list 3200.2625 -181.357) 
(list 3199.7375 -181.357) 
(list 3199.7375 -186.357)))
(apply 'command (append '("pline") coords '("c")))
(setq currobj (ssadd (entlast) currobj))
(command "_layer" "set" "prebias" "")
(command "_rectangle" "3199.7375,-186.357" "3200.2625,-181.357")
(setq currobj (ssadd (entlast) currobj))
(command "_layer" "set" "nitride" "")
(setq coords (list 
(list 3200.2625 -181.357) 
(list 3200.5625 -171.357) 
(list 3200.5625 -171.357) 
(list 3200.5625 -170.357) 
(list 3274.585 -171.107) 
(list 3274.585 -166.164) 
(list 3200.5625 -166.914) 
(list 3200.5625 -165.914) 
(list 3200.5625 -165.914) 
(list 3200.2625 -155.914) 
(list 3199.7375 -155.914) 
(list 3199.4375 -165.914) 
(list 3199.4375 -165.914) 
(list 3199.4375 -166.914) 
(list 3125.415 -166.164) 
(list 3125.415 -171.107) 
(list 3199.4375 -170.357) 
(list 3199.4375 -171.357) 
(list 3199.4375 -171.357) 
(list 3199.7375 -181.357)))
(apply 'command (append '("pline") coords '("c")))
(setq currobj (ssadd (entlast) currobj))
(command "_layer" "set" "prebias" "")
(setq coords (list 
(list 3199.4375 -181.357) 
(list 3199.4375 -170.357) 
(list 3125.415 -171.107) 
(list 3125.415 -166.164) 
(list 3199.4375 -166.914) 
(list 3199.4375 -155.914) 
(list 3200.5625 -155.914) 
(list 3200.5625 -166.914) 
(list 3274.585 -166.164) 
(list 3274.585 -171.107) 
(list 3200.5625 -170.357) 
(list 3200.5625 -181.357)))
(apply 'command (append '("pline") coords '("c")))
(setq currobj (ssadd (entlast) currobj))
(command "_layer" "set" "nitride" "")
(command "_layer" "set" "fda1" "")
(setq coords (list 
(list 3200.5625 -170.214) 
(list 3274.585 -170.964) 
(list 3274.585 -170.787) 
(list 3200.5625 -170.137)))
(apply 'command (append '("pline") coords '("c")))
(setq currobj (ssadd (entlast) currobj))
(setq coords (list 
(list 3200.5625 -169.994) 
(list 3274.585 -170.644) 
(list 3274.585 -170.467) 
(list 3200.5625 -169.917)))
(apply 'command (append '("pline") coords '("c")))
(setq currobj (ssadd (entlast) currobj))
(setq coords (list 
(list 3200.5625 -169.774) 
(list 3274.585 -170.324) 
(list 3274.585 -170.147) 
(list 3200.5625 -169.697)))
(apply 'command (append '("pline") coords '("c")))
(setq currobj (ssadd (entlast) currobj))
(setq coords (list 
(list 3200.5625 -169.554) 
(list 3274.585 -170.004) 
(list 3274.585 -169.827) 
(list 3200.5625 -169.477)))
(apply 'command (append '("pline") coords '("c")))
(setq currobj (ssadd (entlast) currobj))
(setq coords (list 
(list 3200.5625 -169.334) 
(list 3274.585 -169.684) 
(list 3274.585 -169.507) 
(list 3200.5625 -169.257)))
(apply 'command (append '("pline") coords '("c")))
(setq currobj (ssadd (entlast) currobj))
(setq coords (list 
(list 3200.5625 -169.114) 
(list 3274.585 -169.364) 
(list 3274.585 -169.187) 
(list 3200.5625 -169.037)))
(apply 'command (append '("pline") coords '("c")))
(setq currobj (ssadd (entlast) currobj))
(setq coords (list 
(list 3200.5625 -168.894) 
(list 3274.585 -169.044) 
(list 3274.585 -168.867) 
(list 3200.5625 -168.817)))
(apply 'command (append '("pline") coords '("c")))
(setq currobj (ssadd (entlast) currobj))
(setq coords (list 
(list 3200.5625 -168.674) 
(list 3274.585 -168.724) 
(list 3274.585 -168.547) 
(list 3200.5625 -168.597)))
(apply 'command (append '("pline") coords '("c")))
(setq currobj (ssadd (entlast) currobj))
(setq coords (list 
(list 3200.5625 -168.454) 
(list 3274.585 -168.404) 
(list 3274.585 -168.227) 
(list 3200.5625 -168.377)))
(apply 'command (append '("pline") coords '("c")))
(setq currobj (ssadd (entlast) currobj))
(setq coords (list 
(list 3200.5625 -168.234) 
(list 3274.585 -168.084) 
(list 3274.585 -167.907) 
(list 3200.5625 -168.157)))
(apply 'command (append '("pline") coords '("c")))
(setq currobj (ssadd (entlast) currobj))
(setq coords (list 
(list 3200.5625 -168.014) 
(list 3274.585 -167.764) 
(list 3274.585 -167.587) 
(list 3200.5625 -167.937)))
(apply 'command (append '("pline") coords '("c")))
(setq currobj (ssadd (entlast) currobj))
(setq coords (list 
(list 3200.5625 -167.794) 
(list 3274.585 -167.444) 
(list 3274.585 -167.267) 
(list 3200.5625 -167.717)))
(apply 'command (append '("pline") coords '("c")))
(setq currobj (ssadd (entlast) currobj))
(setq coords (list 
(list 3200.5625 -167.574) 
(list 3274.585 -167.124) 
(list 3274.585 -166.947) 
(list 3200.5625 -167.497)))
(apply 'command (append '("pline") coords '("c")))
(setq currobj (ssadd (entlast) currobj))
(setq coords (list 
(list 3200.5625 -167.354) 
(list 3274.585 -166.804) 
(list 3274.585 -166.627) 
(list 3200.5625 -167.277)))
(apply 'command (append '("pline") coords '("c")))
(setq currobj (ssadd (entlast) currobj))
(setq coords (list 
(list 3200.5625 -167.134) 
(list 3274.585 -166.484) 
(list 3274.585 -166.307) 
(list 3200.5625 -167.057)))
(apply 'command (append '("pline") coords '("c")))
(setq currobj (ssadd (entlast) currobj))
(setq coords (list 
(list 3199.4375 -167.057) 
(list 3125.415 -166.307) 
(list 3125.415 -166.484) 
(list 3199.4375 -167.134)))
(apply 'command (append '("pline") coords '("c")))
(setq currobj (ssadd (entlast) currobj))
(setq coords (list 
(list 3199.4375 -167.277) 
(list 3125.415 -166.627) 
(list 3125.415 -166.804) 
(list 3199.4375 -167.354)))
(apply 'command (append '("pline") coords '("c")))
(setq currobj (ssadd (entlast) currobj))
(setq coords (list 
(list 3199.4375 -167.497) 
(list 3125.415 -166.947) 
(list 3125.415 -167.124) 
(list 3199.4375 -167.574)))
(apply 'command (append '("pline") coords '("c")))
(setq currobj (ssadd (entlast) currobj))
(setq coords (list 
(list 3199.4375 -167.717) 
(list 3125.415 -167.267) 
(list 3125.415 -167.444) 
(list 3199.4375 -167.794)))
(apply 'command (append '("pline") coords '("c")))
(setq currobj (ssadd (entlast) currobj))
(setq coords (list 
(list 3199.4375 -167.937) 
(list 3125.415 -167.587) 
(list 3125.415 -167.764) 
(list 3199.4375 -168.014)))
(apply 'command (append '("pline") coords '("c")))
(setq currobj (ssadd (entlast) currobj))
(setq coords (list 
(list 3199.4375 -168.157) 
(list 3125.415 -167.907) 
(list 3125.415 -168.084) 
(list 3199.4375 -168.234)))
(apply 'command (append '("pline") coords '("c")))
(setq currobj (ssadd (entlast) currobj))
(setq coords (list 
(list 3199.4375 -168.377) 
(list 3125.415 -168.227) 
(list 3125.415 -168.404) 
(list 3199.4375 -168.454)))
(apply 'command (append '("pline") coords '("c")))
(setq currobj (ssadd (entlast) currobj))
(setq coords (list 
(list 3199.4375 -168.597) 
(list 3125.415 -168.547) 
(list 3125.415 -168.724) 
(list 3199.4375 -168.674)))
(apply 'command (append '("pline") coords '("c")))
(setq currobj (ssadd (entlast) currobj))
(setq coords (list 
(list 3199.4375 -168.817) 
(list 3125.415 -168.867) 
(list 3125.415 -169.044) 
(list 3199.4375 -168.894)))
(apply 'command (append '("pline") coords '("c")))
(setq currobj (ssadd (entlast) currobj))
(setq coords (list 
(list 3199.4375 -169.037) 
(list 3125.415 -169.187) 
(list 3125.415 -169.364) 
(list 3199.4375 -169.114)))
(apply 'command (append '("pline") coords '("c")))
(setq currobj (ssadd (entlast) currobj))
(setq coords (list 
(list 3199.4375 -169.257) 
(list 3125.415 -169.507) 
(list 3125.415 -169.684) 
(list 3199.4375 -169.334)))
(apply 'command (append '("pline") coords '("c")))
(setq currobj (ssadd (entlast) currobj))
(setq coords (list 
(list 3199.4375 -169.477) 
(list 3125.415 -169.827) 
(list 3125.415 -170.004) 
(list 3199.4375 -169.554)))
(apply 'command (append '("pline") coords '("c")))
(setq currobj (ssadd (entlast) currobj))
(setq coords (list 
(list 3199.4375 -169.697) 
(list 3125.415 -170.147) 
(list 3125.415 -170.324) 
(list 3199.4375 -169.774)))
(apply 'command (append '("pline") coords '("c")))
(setq currobj (ssadd (entlast) currobj))
(setq coords (list 
(list 3199.4375 -169.917) 
(list 3125.415 -170.467) 
(list 3125.415 -170.644) 
(list 3199.4375 -169.994)))
(apply 'command (append '("pline") coords '("c")))
(setq currobj (ssadd (entlast) currobj))
(setq coords (list 
(list 3199.4375 -170.137) 
(list 3125.415 -170.787) 
(list 3125.415 -170.964) 
(list 3199.4375 -170.214)))
(apply 'command (append '("pline") coords '("c")))
(setq currobj (ssadd (entlast) currobj))
(command "_layer" "set" "nitride" "")
(command "_layer" "set" "text" "")
(command "_circle" "3199.0625,-181.357" "0.075")
(command "_circle" "3199.0625,-181.057" "0.075")
(command "_circle" "3199.0625,-180.757" "0.075")
(command "_circle" "3199.0625,-180.457" "0.075")
(command "_circle" "3199.0625,-180.157" "0.075")
(command "_circle" "3198.7625,-181.357" "0.075")
(command "_circle" "3198.7625,-181.057" "0.075")
(command "_circle" "3198.7625,-180.757" "0.075")
(command "_circle" "3198.7625,-180.457" "0.075")
(command "_circle" "3198.7625,-180.157" "0.075")
(command "_circle" "3198.4625,-181.357" "0.075")
(command "_circle" "3198.4625,-181.057" "0.075")
(command "_circle" "3198.4625,-180.757" "0.075")
(command "_circle" "3198.4625,-180.457" "0.075")
(command "_circle" "3198.4625,-180.157" "0.075")
(command "_circle" "3198.1625,-181.357" "0.075")
(command "_circle" "3198.1625,-181.057" "0.075")
(command "_circle" "3198.1625,-180.757" "0.075")
(command "_circle" "3198.1625,-180.457" "0.075")
(command "_circle" "3198.1625,-180.157" "0.075")
(command "_circle" "3197.8625,-181.357" "0.075")
(command "_circle" "3197.8625,-181.057" "0.075")
(command "_circle" "3197.8625,-180.757" "0.075")
(command "_circle" "3197.8625,-180.457" "0.075")
(command "_circle" "3197.8625,-180.157" "0.075")
(command "_layer" "set" "nitride" "")
(setq coords (list 
(list 3200.2625 -155.914) 
(list 3200.2625 -40.2693) 
(list 3199.7375 -40.2693) 
(list 3199.7375 -155.914)))
(apply 'command (append '("pline") coords '("c")))
(setq currobj (ssadd (entlast) currobj))
(command "_layer" "set" "prebias" "")
(command "_rectangle" "3199.7375,-155.914" "3200.2625,-40.2693")
(setq currobj (ssadd (entlast) currobj))
(command "_layer" "set" "nitride" "")
(setq coords (list 
(list 3200.2625 -40.2693) 
(list 3200.5625 -30.2693) 
(list 3200.5625 -30.2693) 
(list 3200.5625 -29.2693) 
(list 3274.585 -30.0193) 
(list 3274.585 -25.0763) 
(list 3200.5625 -25.8263) 
(list 3200.5625 -24.8263) 
(list 3200.5625 -24.8263) 
(list 3200.2625 -14.8263) 
(list 3199.7375 -14.8263) 
(list 3199.4375 -24.8263) 
(list 3199.4375 -24.8263) 
(list 3199.4375 -25.8263) 
(list 3125.415 -25.0763) 
(list 3125.415 -30.0193) 
(list 3199.4375 -29.2693) 
(list 3199.4375 -30.2693) 
(list 3199.4375 -30.2693) 
(list 3199.7375 -40.2693)))
(apply 'command (append '("pline") coords '("c")))
(setq currobj (ssadd (entlast) currobj))
(command "_layer" "set" "prebias" "")
(setq coords (list 
(list 3199.4375 -40.2693) 
(list 3199.4375 -29.2693) 
(list 3125.415 -30.0193) 
(list 3125.415 -25.0763) 
(list 3199.4375 -25.8263) 
(list 3199.4375 -14.8263) 
(list 3200.5625 -14.8263) 
(list 3200.5625 -25.8263) 
(list 3274.585 -25.0763) 
(list 3274.585 -30.0193) 
(list 3200.5625 -29.2693) 
(list 3200.5625 -40.2693)))
(apply 'command (append '("pline") coords '("c")))
(setq currobj (ssadd (entlast) currobj))
(command "_layer" "set" "nitride" "")
(command "_layer" "set" "fda1" "")
(setq coords (list 
(list 3200.5625 -29.1263) 
(list 3274.585 -29.8763) 
(list 3274.585 -29.6993) 
(list 3200.5625 -29.0493)))
(apply 'command (append '("pline") coords '("c")))
(setq currobj (ssadd (entlast) currobj))
(setq coords (list 
(list 3200.5625 -28.9063) 
(list 3274.585 -29.5563) 
(list 3274.585 -29.3793) 
(list 3200.5625 -28.8293)))
(apply 'command (append '("pline") coords '("c")))
(setq currobj (ssadd (entlast) currobj))
(setq coords (list 
(list 3200.5625 -28.6863) 
(list 3274.585 -29.2363) 
(list 3274.585 -29.0593) 
(list 3200.5625 -28.6093)))
(apply 'command (append '("pline") coords '("c")))
(setq currobj (ssadd (entlast) currobj))
(setq coords (list 
(list 3200.5625 -28.4663) 
(list 3274.585 -28.9163) 
(list 3274.585 -28.7393) 
(list 3200.5625 -28.3893)))
(apply 'command (append '("pline") coords '("c")))
(setq currobj (ssadd (entlast) currobj))
(setq coords (list 
(list 3200.5625 -28.2463) 
(list 3274.585 -28.5963) 
(list 3274.585 -28.4193) 
(list 3200.5625 -28.1693)))
(apply 'command (append '("pline") coords '("c")))
(setq currobj (ssadd (entlast) currobj))
(setq coords (list 
(list 3200.5625 -28.0263) 
(list 3274.585 -28.2763) 
(list 3274.585 -28.0993) 
(list 3200.5625 -27.9493)))
(apply 'command (append '("pline") coords '("c")))
(setq currobj (ssadd (entlast) currobj))
(setq coords (list 
(list 3200.5625 -27.8063) 
(list 3274.585 -27.9563) 
(list 3274.585 -27.7793) 
(list 3200.5625 -27.7293)))
(apply 'command (append '("pline") coords '("c")))
(setq currobj (ssadd (entlast) currobj))
(setq coords (list 
(list 3200.5625 -27.5863) 
(list 3274.585 -27.6363) 
(list 3274.585 -27.4593) 
(list 3200.5625 -27.5093)))
(apply 'command (append '("pline") coords '("c")))
(setq currobj (ssadd (entlast) currobj))
(setq coords (list 
(list 3200.5625 -27.3663) 
(list 3274.585 -27.3163) 
(list 3274.585 -27.1393) 
(list 3200.5625 -27.2893)))
(apply 'command (append '("pline") coords '("c")))
(setq currobj (ssadd (entlast) currobj))
(setq coords (list 
(list 3200.5625 -27.1463) 
(list 3274.585 -26.9963) 
(list 3274.585 -26.8193) 
(list 3200.5625 -27.0693)))
(apply 'command (append '("pline") coords '("c")))
(setq currobj (ssadd (entlast) currobj))
(setq coords (list 
(list 3200.5625 -26.9263) 
(list 3274.585 -26.6763) 
(list 3274.585 -26.4993) 
(list 3200.5625 -26.8493)))
(apply 'command (append '("pline") coords '("c")))
(setq currobj (ssadd (entlast) currobj))
(setq coords (list 
(list 3200.5625 -26.7063) 
(list 3274.585 -26.3563) 
(list 3274.585 -26.1793) 
(list 3200.5625 -26.6293)))
(apply 'command (append '("pline") coords '("c")))
(setq currobj (ssadd (entlast) currobj))
(setq coords (list 
(list 3200.5625 -26.4863) 
(list 3274.585 -26.0363) 
(list 3274.585 -25.8593) 
(list 3200.5625 -26.4093)))
(apply 'command (append '("pline") coords '("c")))
(setq currobj (ssadd (entlast) currobj))
(setq coords (list 
(list 3200.5625 -26.2663) 
(list 3274.585 -25.7163) 
(list 3274.585 -25.5393) 
(list 3200.5625 -26.1893)))
(apply 'command (append '("pline") coords '("c")))
(setq currobj (ssadd (entlast) currobj))
(setq coords (list 
(list 3200.5625 -26.0463) 
(list 3274.585 -25.3963) 
(list 3274.585 -25.2193) 
(list 3200.5625 -25.9693)))
(apply 'command (append '("pline") coords '("c")))
(setq currobj (ssadd (entlast) currobj))
(setq coords (list 
(list 3199.4375 -25.9693) 
(list 3125.415 -25.2193) 
(list 3125.415 -25.3963) 
(list 3199.4375 -26.0463)))
(apply 'command (append '("pline") coords '("c")))
(setq currobj (ssadd (entlast) currobj))
(setq coords (list 
(list 3199.4375 -26.1893) 
(list 3125.415 -25.5393) 
(list 3125.415 -25.7163) 
(list 3199.4375 -26.2663)))
(apply 'command (append '("pline") coords '("c")))
(setq currobj (ssadd (entlast) currobj))
(setq coords (list 
(list 3199.4375 -26.4093) 
(list 3125.415 -25.8593) 
(list 3125.415 -26.0363) 
(list 3199.4375 -26.4863)))
(apply 'command (append '("pline") coords '("c")))
(setq currobj (ssadd (entlast) currobj))
(setq coords (list 
(list 3199.4375 -26.6293) 
(list 3125.415 -26.1793) 
(list 3125.415 -26.3563) 
(list 3199.4375 -26.7063)))
(apply 'command (append '("pline") coords '("c")))
(setq currobj (ssadd (entlast) currobj))
(setq coords (list 
(list 3199.4375 -26.8493) 
(list 3125.415 -26.4993) 
(list 3125.415 -26.6763) 
(list 3199.4375 -26.9263)))
(apply 'command (append '("pline") coords '("c")))
(setq currobj (ssadd (entlast) currobj))
(setq coords (list 
(list 3199.4375 -27.0693) 
(list 3125.415 -26.8193) 
(list 3125.415 -26.9963) 
(list 3199.4375 -27.1463)))
(apply 'command (append '("pline") coords '("c")))
(setq currobj (ssadd (entlast) currobj))
(setq coords (list 
(list 3199.4375 -27.2893) 
(list 3125.415 -27.1393) 
(list 3125.415 -27.3163) 
(list 3199.4375 -27.3663)))
(apply 'command (append '("pline") coords '("c")))
(setq currobj (ssadd (entlast) currobj))
(setq coords (list 
(list 3199.4375 -27.5093) 
(list 3125.415 -27.4593) 
(list 3125.415 -27.6363) 
(list 3199.4375 -27.5863)))
(apply 'command (append '("pline") coords '("c")))
(setq currobj (ssadd (entlast) currobj))
(setq coords (list 
(list 3199.4375 -27.7293) 
(list 3125.415 -27.7793) 
(list 3125.415 -27.9563) 
(list 3199.4375 -27.8063)))
(apply 'command (append '("pline") coords '("c")))
(setq currobj (ssadd (entlast) currobj))
(setq coords (list 
(list 3199.4375 -27.9493) 
(list 3125.415 -28.0993) 
(list 3125.415 -28.2763) 
(list 3199.4375 -28.0263)))
(apply 'command (append '("pline") coords '("c")))
(setq currobj (ssadd (entlast) currobj))
(setq coords (list 
(list 3199.4375 -28.1693) 
(list 3125.415 -28.4193) 
(list 3125.415 -28.5963) 
(list 3199.4375 -28.2463)))
(apply 'command (append '("pline") coords '("c")))
(setq currobj (ssadd (entlast) currobj))
(setq coords (list 
(list 3199.4375 -28.3893) 
(list 3125.415 -28.7393) 
(list 3125.415 -28.9163) 
(list 3199.4375 -28.4663)))
(apply 'command (append '("pline") coords '("c")))
(setq currobj (ssadd (entlast) currobj))
(setq coords (list 
(list 3199.4375 -28.6093) 
(list 3125.415 -29.0593) 
(list 3125.415 -29.2363) 
(list 3199.4375 -28.6863)))
(apply 'command (append '("pline") coords '("c")))
(setq currobj (ssadd (entlast) currobj))
(setq coords (list 
(list 3199.4375 -28.8293) 
(list 3125.415 -29.3793) 
(list 3125.415 -29.5563) 
(list 3199.4375 -28.9063)))
(apply 'command (append '("pline") coords '("c")))
(setq currobj (ssadd (entlast) currobj))
(setq coords (list 
(list 3199.4375 -29.0493) 
(list 3125.415 -29.6993) 
(list 3125.415 -29.8763) 
(list 3199.4375 -29.1263)))
(apply 'command (append '("pline") coords '("c")))
(setq currobj (ssadd (entlast) currobj))
(command "_layer" "set" "nitride" "")
(command "_layer" "set" "text" "")
(command "_circle" "3199.0625,-40.2693" "0.075")
(command "_circle" "3199.0625,-39.9693" "0.075")
(command "_circle" "3199.0625,-39.6693" "0.075")
(command "_circle" "3199.0625,-39.3693" "0.075")
(command "_circle" "3199.0625,-39.0693" "0.075")
(command "_circle" "3198.7625,-40.2693" "0.075")
(command "_circle" "3198.7625,-39.9693" "0.075")
(command "_circle" "3198.7625,-39.6693" "0.075")
(command "_circle" "3198.7625,-39.3693" "0.075")
(command "_circle" "3198.7625,-39.0693" "0.075")
(command "_circle" "3198.4625,-40.2693" "0.075")
(command "_circle" "3198.4625,-39.9693" "0.075")
(command "_circle" "3198.4625,-39.6693" "0.075")
(command "_circle" "3198.4625,-39.3693" "0.075")
(command "_circle" "3198.4625,-39.0693" "0.075")
(command "_circle" "3198.1625,-40.2693" "0.075")
(command "_circle" "3198.1625,-39.9693" "0.075")
(command "_circle" "3198.1625,-39.6693" "0.075")
(command "_circle" "3198.1625,-39.3693" "0.075")
(command "_circle" "3198.1625,-39.0693" "0.075")
(command "_circle" "3197.8625,-40.2693" "0.075")
(command "_circle" "3197.8625,-39.9693" "0.075")
(command "_circle" "3197.8625,-39.6693" "0.075")
(command "_circle" "3197.8625,-39.3693" "0.075")
(command "_circle" "3197.8625,-39.0693" "0.075")
(command "_layer" "set" "nitride" "")
(setq coords (list 
(list 3200.2625 -14.8263) 
(list 3200.2625 100.8184) 
(list 3199.7375 100.8184) 
(list 3199.7375 -14.8263)))
(apply 'command (append '("pline") coords '("c")))
(setq currobj (ssadd (entlast) currobj))
(command "_layer" "set" "prebias" "")
(command "_rectangle" "3199.7375,-14.8263" "3200.2625,100.8184")
(setq currobj (ssadd (entlast) currobj))
(command "_layer" "set" "nitride" "")
(setq coords (list 
(list 3200.2625 100.8184) 
(list 3200.5625 110.8184) 
(list 3200.5625 110.8184) 
(list 3200.5625 111.8184) 
(list 3274.585 111.0684) 
(list 3274.585 116.0114) 
(list 3200.5625 115.2614) 
(list 3200.5625 116.2614) 
(list 3200.5625 116.2614) 
(list 3200.2625 126.2614) 
(list 3199.7375 126.2614) 
(list 3199.4375 116.2614) 
(list 3199.4375 116.2614) 
(list 3199.4375 115.2614) 
(list 3125.415 116.0114) 
(list 3125.415 111.0684) 
(list 3199.4375 111.8184) 
(list 3199.4375 110.8184) 
(list 3199.4375 110.8184) 
(list 3199.7375 100.8184)))
(apply 'command (append '("pline") coords '("c")))
(setq currobj (ssadd (entlast) currobj))
(command "_layer" "set" "prebias" "")
(setq coords (list 
(list 3199.4375 100.8184) 
(list 3199.4375 111.8184) 
(list 3125.415 111.0684) 
(list 3125.415 116.0114) 
(list 3199.4375 115.2614) 
(list 3199.4375 126.2614) 
(list 3200.5625 126.2614) 
(list 3200.5625 115.2614) 
(list 3274.585 116.0114) 
(list 3274.585 111.0684) 
(list 3200.5625 111.8184) 
(list 3200.5625 100.8184)))
(apply 'command (append '("pline") coords '("c")))
(setq currobj (ssadd (entlast) currobj))
(command "_layer" "set" "nitride" "")
(command "_layer" "set" "fda1" "")
(setq coords (list 
(list 3200.5625 111.9614) 
(list 3274.585 111.2114) 
(list 3274.585 111.3884) 
(list 3200.5625 112.0384)))
(apply 'command (append '("pline") coords '("c")))
(setq currobj (ssadd (entlast) currobj))
(setq coords (list 
(list 3200.5625 112.1814) 
(list 3274.585 111.5314) 
(list 3274.585 111.7084) 
(list 3200.5625 112.2584)))
(apply 'command (append '("pline") coords '("c")))
(setq currobj (ssadd (entlast) currobj))
(setq coords (list 
(list 3200.5625 112.4014) 
(list 3274.585 111.8514) 
(list 3274.585 112.0284) 
(list 3200.5625 112.4784)))
(apply 'command (append '("pline") coords '("c")))
(setq currobj (ssadd (entlast) currobj))
(setq coords (list 
(list 3200.5625 112.6214) 
(list 3274.585 112.1714) 
(list 3274.585 112.3484) 
(list 3200.5625 112.6984)))
(apply 'command (append '("pline") coords '("c")))
(setq currobj (ssadd (entlast) currobj))
(setq coords (list 
(list 3200.5625 112.8414) 
(list 3274.585 112.4914) 
(list 3274.585 112.6684) 
(list 3200.5625 112.9184)))
(apply 'command (append '("pline") coords '("c")))
(setq currobj (ssadd (entlast) currobj))
(setq coords (list 
(list 3200.5625 113.0614) 
(list 3274.585 112.8114) 
(list 3274.585 112.9884) 
(list 3200.5625 113.1384)))
(apply 'command (append '("pline") coords '("c")))
(setq currobj (ssadd (entlast) currobj))
(setq coords (list 
(list 3200.5625 113.2814) 
(list 3274.585 113.1314) 
(list 3274.585 113.3084) 
(list 3200.5625 113.3584)))
(apply 'command (append '("pline") coords '("c")))
(setq currobj (ssadd (entlast) currobj))
(setq coords (list 
(list 3200.5625 113.5014) 
(list 3274.585 113.4514) 
(list 3274.585 113.6284) 
(list 3200.5625 113.5784)))
(apply 'command (append '("pline") coords '("c")))
(setq currobj (ssadd (entlast) currobj))
(setq coords (list 
(list 3200.5625 113.7214) 
(list 3274.585 113.7714) 
(list 3274.585 113.9484) 
(list 3200.5625 113.7984)))
(apply 'command (append '("pline") coords '("c")))
(setq currobj (ssadd (entlast) currobj))
(setq coords (list 
(list 3200.5625 113.9414) 
(list 3274.585 114.0914) 
(list 3274.585 114.2684) 
(list 3200.5625 114.0184)))
(apply 'command (append '("pline") coords '("c")))
(setq currobj (ssadd (entlast) currobj))
(setq coords (list 
(list 3200.5625 114.1614) 
(list 3274.585 114.4114) 
(list 3274.585 114.5884) 
(list 3200.5625 114.2384)))
(apply 'command (append '("pline") coords '("c")))
(setq currobj (ssadd (entlast) currobj))
(setq coords (list 
(list 3200.5625 114.3814) 
(list 3274.585 114.7314) 
(list 3274.585 114.9084) 
(list 3200.5625 114.4584)))
(apply 'command (append '("pline") coords '("c")))
(setq currobj (ssadd (entlast) currobj))
(setq coords (list 
(list 3200.5625 114.6014) 
(list 3274.585 115.0514) 
(list 3274.585 115.2284) 
(list 3200.5625 114.6784)))
(apply 'command (append '("pline") coords '("c")))
(setq currobj (ssadd (entlast) currobj))
(setq coords (list 
(list 3200.5625 114.8214) 
(list 3274.585 115.3714) 
(list 3274.585 115.5484) 
(list 3200.5625 114.8984)))
(apply 'command (append '("pline") coords '("c")))
(setq currobj (ssadd (entlast) currobj))
(setq coords (list 
(list 3200.5625 115.0414) 
(list 3274.585 115.6914) 
(list 3274.585 115.8684) 
(list 3200.5625 115.1184)))
(apply 'command (append '("pline") coords '("c")))
(setq currobj (ssadd (entlast) currobj))
(setq coords (list 
(list 3199.4375 115.1184) 
(list 3125.415 115.8684) 
(list 3125.415 115.6914) 
(list 3199.4375 115.0414)))
(apply 'command (append '("pline") coords '("c")))
(setq currobj (ssadd (entlast) currobj))
(setq coords (list 
(list 3199.4375 114.8984) 
(list 3125.415 115.5484) 
(list 3125.415 115.3714) 
(list 3199.4375 114.8214)))
(apply 'command (append '("pline") coords '("c")))
(setq currobj (ssadd (entlast) currobj))
(setq coords (list 
(list 3199.4375 114.6784) 
(list 3125.415 115.2284) 
(list 3125.415 115.0514) 
(list 3199.4375 114.6014)))
(apply 'command (append '("pline") coords '("c")))
(setq currobj (ssadd (entlast) currobj))
(setq coords (list 
(list 3199.4375 114.4584) 
(list 3125.415 114.9084) 
(list 3125.415 114.7314) 
(list 3199.4375 114.3814)))
(apply 'command (append '("pline") coords '("c")))
(setq currobj (ssadd (entlast) currobj))
(setq coords (list 
(list 3199.4375 114.2384) 
(list 3125.415 114.5884) 
(list 3125.415 114.4114) 
(list 3199.4375 114.1614)))
(apply 'command (append '("pline") coords '("c")))
(setq currobj (ssadd (entlast) currobj))
(setq coords (list 
(list 3199.4375 114.0184) 
(list 3125.415 114.2684) 
(list 3125.415 114.0914) 
(list 3199.4375 113.9414)))
(apply 'command (append '("pline") coords '("c")))
(setq currobj (ssadd (entlast) currobj))
(setq coords (list 
(list 3199.4375 113.7984) 
(list 3125.415 113.9484) 
(list 3125.415 113.7714) 
(list 3199.4375 113.7214)))
(apply 'command (append '("pline") coords '("c")))
(setq currobj (ssadd (entlast) currobj))
(setq coords (list 
(list 3199.4375 113.5784) 
(list 3125.415 113.6284) 
(list 3125.415 113.4514) 
(list 3199.4375 113.5014)))
(apply 'command (append '("pline") coords '("c")))
(setq currobj (ssadd (entlast) currobj))
(setq coords (list 
(list 3199.4375 113.3584) 
(list 3125.415 113.3084) 
(list 3125.415 113.1314) 
(list 3199.4375 113.2814)))
(apply 'command (append '("pline") coords '("c")))
(setq currobj (ssadd (entlast) currobj))
(setq coords (list 
(list 3199.4375 113.1384) 
(list 3125.415 112.9884) 
(list 3125.415 112.8114) 
(list 3199.4375 113.0614)))
(apply 'command (append '("pline") coords '("c")))
(setq currobj (ssadd (entlast) currobj))
(setq coords (list 
(list 3199.4375 112.9184) 
(list 3125.415 112.6684) 
(list 3125.415 112.4914) 
(list 3199.4375 112.8414)))
(apply 'command (append '("pline") coords '("c")))
(setq currobj (ssadd (entlast) currobj))
(setq coords (list 
(list 3199.4375 112.6984) 
(list 3125.415 112.3484) 
(list 3125.415 112.1714) 
(list 3199.4375 112.6214)))
(apply 'command (append '("pline") coords '("c")))
(setq currobj (ssadd (entlast) currobj))
(setq coords (list 
(list 3199.4375 112.4784) 
(list 3125.415 112.0284) 
(list 3125.415 111.8514) 
(list 3199.4375 112.4014)))
(apply 'command (append '("pline") coords '("c")))
(setq currobj (ssadd (entlast) currobj))
(setq coords (list 
(list 3199.4375 112.2584) 
(list 3125.415 111.7084) 
(list 3125.415 111.5314) 
(list 3199.4375 112.1814)))
(apply 'command (append '("pline") coords '("c")))
(setq currobj (ssadd (entlast) currobj))
(setq coords (list 
(list 3199.4375 112.0384) 
(list 3125.415 111.3884) 
(list 3125.415 111.2114) 
(list 3199.4375 111.9614)))
(apply 'command (append '("pline") coords '("c")))
(setq currobj (ssadd (entlast) currobj))
(command "_layer" "set" "nitride" "")
(command "_layer" "set" "text" "")
(command "_circle" "3199.0625,100.8184" "0.075")
(command "_circle" "3199.0625,101.1184" "0.075")
(command "_circle" "3199.0625,101.4184" "0.075")
(command "_circle" "3199.0625,101.7184" "0.075")
(command "_circle" "3199.0625,102.0184" "0.075")
(command "_circle" "3198.7625,100.8184" "0.075")
(command "_circle" "3198.7625,101.1184" "0.075")
(command "_circle" "3198.7625,101.4184" "0.075")
(command "_circle" "3198.7625,101.7184" "0.075")
(command "_circle" "3198.7625,102.0184" "0.075")
(command "_circle" "3198.4625,100.8184" "0.075")
(command "_circle" "3198.4625,101.1184" "0.075")
(command "_circle" "3198.4625,101.4184" "0.075")
(command "_circle" "3198.4625,101.7184" "0.075")
(command "_circle" "3198.4625,102.0184" "0.075")
(command "_circle" "3198.1625,100.8184" "0.075")
(command "_circle" "3198.1625,101.1184" "0.075")
(command "_circle" "3198.1625,101.4184" "0.075")
(command "_circle" "3198.1625,101.7184" "0.075")
(command "_circle" "3198.1625,102.0184" "0.075")
(command "_circle" "3197.8625,100.8184" "0.075")
(command "_circle" "3197.8625,101.1184" "0.075")
(command "_circle" "3197.8625,101.4184" "0.075")
(command "_circle" "3197.8625,101.7184" "0.075")
(command "_circle" "3197.8625,102.0184" "0.075")
(command "_layer" "set" "nitride" "")
(setq coords (list 
(list 3200.2625 126.2614) 
(list 3200.2625 241.9061) 
(list 3199.7375 241.9061) 
(list 3199.7375 126.2614)))
(apply 'command (append '("pline") coords '("c")))
(setq currobj (ssadd (entlast) currobj))
(command "_layer" "set" "prebias" "")
(command "_rectangle" "3199.7375,126.2614" "3200.2625,241.9061")
(setq currobj (ssadd (entlast) currobj))
(command "_layer" "set" "nitride" "")
(setq coords (list 
(list 3200.2625 241.9061) 
(list 3200.5625 251.9061) 
(list 3200.5625 251.9061) 
(list 3200.5625 252.9061) 
(list 3274.585 252.1561) 
(list 3274.585 257.0991) 
(list 3200.5625 256.3491) 
(list 3200.5625 257.3491) 
(list 3200.5625 257.3491) 
(list 3200.2625 267.3491) 
(list 3199.7375 267.3491) 
(list 3199.4375 257.3491) 
(list 3199.4375 257.3491) 
(list 3199.4375 256.3491) 
(list 3125.415 257.0991) 
(list 3125.415 252.1561) 
(list 3199.4375 252.9061) 
(list 3199.4375 251.9061) 
(list 3199.4375 251.9061) 
(list 3199.7375 241.9061)))
(apply 'command (append '("pline") coords '("c")))
(setq currobj (ssadd (entlast) currobj))
(command "_layer" "set" "prebias" "")
(setq coords (list 
(list 3199.4375 241.9061) 
(list 3199.4375 252.9061) 
(list 3125.415 252.1561) 
(list 3125.415 257.0991) 
(list 3199.4375 256.3491) 
(list 3199.4375 267.3491) 
(list 3200.5625 267.3491) 
(list 3200.5625 256.3491) 
(list 3274.585 257.0991) 
(list 3274.585 252.1561) 
(list 3200.5625 252.9061) 
(list 3200.5625 241.9061)))
(apply 'command (append '("pline") coords '("c")))
(setq currobj (ssadd (entlast) currobj))
(command "_layer" "set" "nitride" "")
(command "_layer" "set" "fda1" "")
(setq coords (list 
(list 3200.5625 253.0491) 
(list 3274.585 252.2991) 
(list 3274.585 252.4761) 
(list 3200.5625 253.1261)))
(apply 'command (append '("pline") coords '("c")))
(setq currobj (ssadd (entlast) currobj))
(setq coords (list 
(list 3200.5625 253.2691) 
(list 3274.585 252.6191) 
(list 3274.585 252.7961) 
(list 3200.5625 253.3461)))
(apply 'command (append '("pline") coords '("c")))
(setq currobj (ssadd (entlast) currobj))
(setq coords (list 
(list 3200.5625 253.4891) 
(list 3274.585 252.9391) 
(list 3274.585 253.1161) 
(list 3200.5625 253.5661)))
(apply 'command (append '("pline") coords '("c")))
(setq currobj (ssadd (entlast) currobj))
(setq coords (list 
(list 3200.5625 253.7091) 
(list 3274.585 253.2591) 
(list 3274.585 253.4361) 
(list 3200.5625 253.7861)))
(apply 'command (append '("pline") coords '("c")))
(setq currobj (ssadd (entlast) currobj))
(setq coords (list 
(list 3200.5625 253.9291) 
(list 3274.585 253.5791) 
(list 3274.585 253.7561) 
(list 3200.5625 254.0061)))
(apply 'command (append '("pline") coords '("c")))
(setq currobj (ssadd (entlast) currobj))
(setq coords (list 
(list 3200.5625 254.1491) 
(list 3274.585 253.8991) 
(list 3274.585 254.0761) 
(list 3200.5625 254.2261)))
(apply 'command (append '("pline") coords '("c")))
(setq currobj (ssadd (entlast) currobj))
(setq coords (list 
(list 3200.5625 254.3691) 
(list 3274.585 254.2191) 
(list 3274.585 254.3961) 
(list 3200.5625 254.4461)))
(apply 'command (append '("pline") coords '("c")))
(setq currobj (ssadd (entlast) currobj))
(setq coords (list 
(list 3200.5625 254.5891) 
(list 3274.585 254.5391) 
(list 3274.585 254.7161) 
(list 3200.5625 254.6661)))
(apply 'command (append '("pline") coords '("c")))
(setq currobj (ssadd (entlast) currobj))
(setq coords (list 
(list 3200.5625 254.8091) 
(list 3274.585 254.8591) 
(list 3274.585 255.0361) 
(list 3200.5625 254.8861)))
(apply 'command (append '("pline") coords '("c")))
(setq currobj (ssadd (entlast) currobj))
(setq coords (list 
(list 3200.5625 255.0291) 
(list 3274.585 255.1791) 
(list 3274.585 255.3561) 
(list 3200.5625 255.1061)))
(apply 'command (append '("pline") coords '("c")))
(setq currobj (ssadd (entlast) currobj))
(setq coords (list 
(list 3200.5625 255.2491) 
(list 3274.585 255.4991) 
(list 3274.585 255.6761) 
(list 3200.5625 255.3261)))
(apply 'command (append '("pline") coords '("c")))
(setq currobj (ssadd (entlast) currobj))
(setq coords (list 
(list 3200.5625 255.4691) 
(list 3274.585 255.8191) 
(list 3274.585 255.9961) 
(list 3200.5625 255.5461)))
(apply 'command (append '("pline") coords '("c")))
(setq currobj (ssadd (entlast) currobj))
(setq coords (list 
(list 3200.5625 255.6891) 
(list 3274.585 256.1391) 
(list 3274.585 256.3161) 
(list 3200.5625 255.7661)))
(apply 'command (append '("pline") coords '("c")))
(setq currobj (ssadd (entlast) currobj))
(setq coords (list 
(list 3200.5625 255.9091) 
(list 3274.585 256.4591) 
(list 3274.585 256.6361) 
(list 3200.5625 255.9861)))
(apply 'command (append '("pline") coords '("c")))
(setq currobj (ssadd (entlast) currobj))
(setq coords (list 
(list 3200.5625 256.1291) 
(list 3274.585 256.7791) 
(list 3274.585 256.9561) 
(list 3200.5625 256.2061)))
(apply 'command (append '("pline") coords '("c")))
(setq currobj (ssadd (entlast) currobj))
(setq coords (list 
(list 3199.4375 256.2061) 
(list 3125.415 256.9561) 
(list 3125.415 256.7791) 
(list 3199.4375 256.1291)))
(apply 'command (append '("pline") coords '("c")))
(setq currobj (ssadd (entlast) currobj))
(setq coords (list 
(list 3199.4375 255.9861) 
(list 3125.415 256.6361) 
(list 3125.415 256.4591) 
(list 3199.4375 255.9091)))
(apply 'command (append '("pline") coords '("c")))
(setq currobj (ssadd (entlast) currobj))
(setq coords (list 
(list 3199.4375 255.7661) 
(list 3125.415 256.3161) 
(list 3125.415 256.1391) 
(list 3199.4375 255.6891)))
(apply 'command (append '("pline") coords '("c")))
(setq currobj (ssadd (entlast) currobj))
(setq coords (list 
(list 3199.4375 255.5461) 
(list 3125.415 255.9961) 
(list 3125.415 255.8191) 
(list 3199.4375 255.4691)))
(apply 'command (append '("pline") coords '("c")))
(setq currobj (ssadd (entlast) currobj))
(setq coords (list 
(list 3199.4375 255.3261) 
(list 3125.415 255.6761) 
(list 3125.415 255.4991) 
(list 3199.4375 255.2491)))
(apply 'command (append '("pline") coords '("c")))
(setq currobj (ssadd (entlast) currobj))
(setq coords (list 
(list 3199.4375 255.1061) 
(list 3125.415 255.3561) 
(list 3125.415 255.1791) 
(list 3199.4375 255.0291)))
(apply 'command (append '("pline") coords '("c")))
(setq currobj (ssadd (entlast) currobj))
(setq coords (list 
(list 3199.4375 254.8861) 
(list 3125.415 255.0361) 
(list 3125.415 254.8591) 
(list 3199.4375 254.8091)))
(apply 'command (append '("pline") coords '("c")))
(setq currobj (ssadd (entlast) currobj))
(setq coords (list 
(list 3199.4375 254.6661) 
(list 3125.415 254.7161) 
(list 3125.415 254.5391) 
(list 3199.4375 254.5891)))
(apply 'command (append '("pline") coords '("c")))
(setq currobj (ssadd (entlast) currobj))
(setq coords (list 
(list 3199.4375 254.4461) 
(list 3125.415 254.3961) 
(list 3125.415 254.2191) 
(list 3199.4375 254.3691)))
(apply 'command (append '("pline") coords '("c")))
(setq currobj (ssadd (entlast) currobj))
(setq coords (list 
(list 3199.4375 254.2261) 
(list 3125.415 254.0761) 
(list 3125.415 253.8991) 
(list 3199.4375 254.1491)))
(apply 'command (append '("pline") coords '("c")))
(setq currobj (ssadd (entlast) currobj))
(setq coords (list 
(list 3199.4375 254.0061) 
(list 3125.415 253.7561) 
(list 3125.415 253.5791) 
(list 3199.4375 253.9291)))
(apply 'command (append '("pline") coords '("c")))
(setq currobj (ssadd (entlast) currobj))
(setq coords (list 
(list 3199.4375 253.7861) 
(list 3125.415 253.4361) 
(list 3125.415 253.2591) 
(list 3199.4375 253.7091)))
(apply 'command (append '("pline") coords '("c")))
(setq currobj (ssadd (entlast) currobj))
(setq coords (list 
(list 3199.4375 253.5661) 
(list 3125.415 253.1161) 
(list 3125.415 252.9391) 
(list 3199.4375 253.4891)))
(apply 'command (append '("pline") coords '("c")))
(setq currobj (ssadd (entlast) currobj))
(setq coords (list 
(list 3199.4375 253.3461) 
(list 3125.415 252.7961) 
(list 3125.415 252.6191) 
(list 3199.4375 253.2691)))
(apply 'command (append '("pline") coords '("c")))
(setq currobj (ssadd (entlast) currobj))
(setq coords (list 
(list 3199.4375 253.1261) 
(list 3125.415 252.4761) 
(list 3125.415 252.2991) 
(list 3199.4375 253.0491)))
(apply 'command (append '("pline") coords '("c")))
(setq currobj (ssadd (entlast) currobj))
(command "_layer" "set" "nitride" "")
(command "_layer" "set" "text" "")
(command "_circle" "3199.0625,241.9061" "0.075")
(command "_circle" "3199.0625,242.2061" "0.075")
(command "_circle" "3199.0625,242.5061" "0.075")
(command "_circle" "3199.0625,242.8061" "0.075")
(command "_circle" "3199.0625,243.1061" "0.075")
(command "_circle" "3198.7625,241.9061" "0.075")
(command "_circle" "3198.7625,242.2061" "0.075")
(command "_circle" "3198.7625,242.5061" "0.075")
(command "_circle" "3198.7625,242.8061" "0.075")
(command "_circle" "3198.7625,243.1061" "0.075")
(command "_circle" "3198.4625,241.9061" "0.075")
(command "_circle" "3198.4625,242.2061" "0.075")
(command "_circle" "3198.4625,242.5061" "0.075")
(command "_circle" "3198.4625,242.8061" "0.075")
(command "_circle" "3198.4625,243.1061" "0.075")
(command "_circle" "3198.1625,241.9061" "0.075")
(command "_circle" "3198.1625,242.2061" "0.075")
(command "_circle" "3198.1625,242.5061" "0.075")
(command "_circle" "3198.1625,242.8061" "0.075")
(command "_circle" "3198.1625,243.1061" "0.075")
(command "_circle" "3197.8625,241.9061" "0.075")
(command "_circle" "3197.8625,242.2061" "0.075")
(command "_circle" "3197.8625,242.5061" "0.075")
(command "_circle" "3197.8625,242.8061" "0.075")
(command "_circle" "3197.8625,243.1061" "0.075")
(command "_layer" "set" "nitride" "")
(setq coords (list 
(list 3200.2625 267.3491) 
(list 3200.2625 382.9939) 
(list 3199.7375 382.9939) 
(list 3199.7375 267.3491)))
(apply 'command (append '("pline") coords '("c")))
(setq currobj (ssadd (entlast) currobj))
(command "_layer" "set" "prebias" "")
(command "_rectangle" "3199.7375,267.3491" "3200.2625,382.9939")
(setq currobj (ssadd (entlast) currobj))
(command "_layer" "set" "nitride" "")
(setq coords (list 
(list 3200.2625 382.9939) 
(list 3200.5625 392.9939) 
(list 3200.5625 392.9939) 
(list 3200.5625 393.9939) 
(list 3274.585 393.2439) 
(list 3274.585 398.1869) 
(list 3200.5625 397.4369) 
(list 3200.5625 398.4369) 
(list 3200.5625 398.4369) 
(list 3200.2625 408.4369) 
(list 3199.7375 408.4369) 
(list 3199.4375 398.4369) 
(list 3199.4375 398.4369) 
(list 3199.4375 397.4369) 
(list 3125.415 398.1869) 
(list 3125.415 393.2439) 
(list 3199.4375 393.9939) 
(list 3199.4375 392.9939) 
(list 3199.4375 392.9939) 
(list 3199.7375 382.9939)))
(apply 'command (append '("pline") coords '("c")))
(setq currobj (ssadd (entlast) currobj))
(command "_layer" "set" "prebias" "")
(setq coords (list 
(list 3199.4375 382.9939) 
(list 3199.4375 393.9939) 
(list 3125.415 393.2439) 
(list 3125.415 398.1869) 
(list 3199.4375 397.4369) 
(list 3199.4375 408.4369) 
(list 3200.5625 408.4369) 
(list 3200.5625 397.4369) 
(list 3274.585 398.1869) 
(list 3274.585 393.2439) 
(list 3200.5625 393.9939) 
(list 3200.5625 382.9939)))
(apply 'command (append '("pline") coords '("c")))
(setq currobj (ssadd (entlast) currobj))
(command "_layer" "set" "nitride" "")
(command "_layer" "set" "fda1" "")
(setq coords (list 
(list 3200.5625 394.1369) 
(list 3274.585 393.3869) 
(list 3274.585 393.5639) 
(list 3200.5625 394.2139)))
(apply 'command (append '("pline") coords '("c")))
(setq currobj (ssadd (entlast) currobj))
(setq coords (list 
(list 3200.5625 394.3569) 
(list 3274.585 393.7069) 
(list 3274.585 393.8839) 
(list 3200.5625 394.4339)))
(apply 'command (append '("pline") coords '("c")))
(setq currobj (ssadd (entlast) currobj))
(setq coords (list 
(list 3200.5625 394.5769) 
(list 3274.585 394.0269) 
(list 3274.585 394.2039) 
(list 3200.5625 394.6539)))
(apply 'command (append '("pline") coords '("c")))
(setq currobj (ssadd (entlast) currobj))
(setq coords (list 
(list 3200.5625 394.7969) 
(list 3274.585 394.3469) 
(list 3274.585 394.5239) 
(list 3200.5625 394.8739)))
(apply 'command (append '("pline") coords '("c")))
(setq currobj (ssadd (entlast) currobj))
(setq coords (list 
(list 3200.5625 395.0169) 
(list 3274.585 394.6669) 
(list 3274.585 394.8439) 
(list 3200.5625 395.0939)))
(apply 'command (append '("pline") coords '("c")))
(setq currobj (ssadd (entlast) currobj))
(setq coords (list 
(list 3200.5625 395.2369) 
(list 3274.585 394.9869) 
(list 3274.585 395.1639) 
(list 3200.5625 395.3139)))
(apply 'command (append '("pline") coords '("c")))
(setq currobj (ssadd (entlast) currobj))
(setq coords (list 
(list 3200.5625 395.4569) 
(list 3274.585 395.3069) 
(list 3274.585 395.4839) 
(list 3200.5625 395.5339)))
(apply 'command (append '("pline") coords '("c")))
(setq currobj (ssadd (entlast) currobj))
(setq coords (list 
(list 3200.5625 395.6769) 
(list 3274.585 395.6269) 
(list 3274.585 395.8039) 
(list 3200.5625 395.7539)))
(apply 'command (append '("pline") coords '("c")))
(setq currobj (ssadd (entlast) currobj))
(setq coords (list 
(list 3200.5625 395.8969) 
(list 3274.585 395.9469) 
(list 3274.585 396.1239) 
(list 3200.5625 395.9739)))
(apply 'command (append '("pline") coords '("c")))
(setq currobj (ssadd (entlast) currobj))
(setq coords (list 
(list 3200.5625 396.1169) 
(list 3274.585 396.2669) 
(list 3274.585 396.4439) 
(list 3200.5625 396.1939)))
(apply 'command (append '("pline") coords '("c")))
(setq currobj (ssadd (entlast) currobj))
(setq coords (list 
(list 3200.5625 396.3369) 
(list 3274.585 396.5869) 
(list 3274.585 396.7639) 
(list 3200.5625 396.4139)))
(apply 'command (append '("pline") coords '("c")))
(setq currobj (ssadd (entlast) currobj))
(setq coords (list 
(list 3200.5625 396.5569) 
(list 3274.585 396.9069) 
(list 3274.585 397.0839) 
(list 3200.5625 396.6339)))
(apply 'command (append '("pline") coords '("c")))
(setq currobj (ssadd (entlast) currobj))
(setq coords (list 
(list 3200.5625 396.7769) 
(list 3274.585 397.2269) 
(list 3274.585 397.4039) 
(list 3200.5625 396.8539)))
(apply 'command (append '("pline") coords '("c")))
(setq currobj (ssadd (entlast) currobj))
(setq coords (list 
(list 3200.5625 396.9969) 
(list 3274.585 397.5469) 
(list 3274.585 397.7239) 
(list 3200.5625 397.0739)))
(apply 'command (append '("pline") coords '("c")))
(setq currobj (ssadd (entlast) currobj))
(setq coords (list 
(list 3200.5625 397.2169) 
(list 3274.585 397.8669) 
(list 3274.585 398.0439) 
(list 3200.5625 397.2939)))
(apply 'command (append '("pline") coords '("c")))
(setq currobj (ssadd (entlast) currobj))
(setq coords (list 
(list 3199.4375 397.2939) 
(list 3125.415 398.0439) 
(list 3125.415 397.8669) 
(list 3199.4375 397.2169)))
(apply 'command (append '("pline") coords '("c")))
(setq currobj (ssadd (entlast) currobj))
(setq coords (list 
(list 3199.4375 397.0739) 
(list 3125.415 397.7239) 
(list 3125.415 397.5469) 
(list 3199.4375 396.9969)))
(apply 'command (append '("pline") coords '("c")))
(setq currobj (ssadd (entlast) currobj))
(setq coords (list 
(list 3199.4375 396.8539) 
(list 3125.415 397.4039) 
(list 3125.415 397.2269) 
(list 3199.4375 396.7769)))
(apply 'command (append '("pline") coords '("c")))
(setq currobj (ssadd (entlast) currobj))
(setq coords (list 
(list 3199.4375 396.6339) 
(list 3125.415 397.0839) 
(list 3125.415 396.9069) 
(list 3199.4375 396.5569)))
(apply 'command (append '("pline") coords '("c")))
(setq currobj (ssadd (entlast) currobj))
(setq coords (list 
(list 3199.4375 396.4139) 
(list 3125.415 396.7639) 
(list 3125.415 396.5869) 
(list 3199.4375 396.3369)))
(apply 'command (append '("pline") coords '("c")))
(setq currobj (ssadd (entlast) currobj))
(setq coords (list 
(list 3199.4375 396.1939) 
(list 3125.415 396.4439) 
(list 3125.415 396.2669) 
(list 3199.4375 396.1169)))
(apply 'command (append '("pline") coords '("c")))
(setq currobj (ssadd (entlast) currobj))
(setq coords (list 
(list 3199.4375 395.9739) 
(list 3125.415 396.1239) 
(list 3125.415 395.9469) 
(list 3199.4375 395.8969)))
(apply 'command (append '("pline") coords '("c")))
(setq currobj (ssadd (entlast) currobj))
(setq coords (list 
(list 3199.4375 395.7539) 
(list 3125.415 395.8039) 
(list 3125.415 395.6269) 
(list 3199.4375 395.6769)))
(apply 'command (append '("pline") coords '("c")))
(setq currobj (ssadd (entlast) currobj))
(setq coords (list 
(list 3199.4375 395.5339) 
(list 3125.415 395.4839) 
(list 3125.415 395.3069) 
(list 3199.4375 395.4569)))
(apply 'command (append '("pline") coords '("c")))
(setq currobj (ssadd (entlast) currobj))
(setq coords (list 
(list 3199.4375 395.3139) 
(list 3125.415 395.1639) 
(list 3125.415 394.9869) 
(list 3199.4375 395.2369)))
(apply 'command (append '("pline") coords '("c")))
(setq currobj (ssadd (entlast) currobj))
(setq coords (list 
(list 3199.4375 395.0939) 
(list 3125.415 394.8439) 
(list 3125.415 394.6669) 
(list 3199.4375 395.0169)))
(apply 'command (append '("pline") coords '("c")))
(setq currobj (ssadd (entlast) currobj))
(setq coords (list 
(list 3199.4375 394.8739) 
(list 3125.415 394.5239) 
(list 3125.415 394.3469) 
(list 3199.4375 394.7969)))
(apply 'command (append '("pline") coords '("c")))
(setq currobj (ssadd (entlast) currobj))
(setq coords (list 
(list 3199.4375 394.6539) 
(list 3125.415 394.2039) 
(list 3125.415 394.0269) 
(list 3199.4375 394.5769)))
(apply 'command (append '("pline") coords '("c")))
(setq currobj (ssadd (entlast) currobj))
(setq coords (list 
(list 3199.4375 394.4339) 
(list 3125.415 393.8839) 
(list 3125.415 393.7069) 
(list 3199.4375 394.3569)))
(apply 'command (append '("pline") coords '("c")))
(setq currobj (ssadd (entlast) currobj))
(setq coords (list 
(list 3199.4375 394.2139) 
(list 3125.415 393.5639) 
(list 3125.415 393.3869) 
(list 3199.4375 394.1369)))
(apply 'command (append '("pline") coords '("c")))
(setq currobj (ssadd (entlast) currobj))
(command "_layer" "set" "nitride" "")
(command "_layer" "set" "text" "")
(command "_circle" "3199.0625,382.9939" "0.075")
(command "_circle" "3199.0625,383.2939" "0.075")
(command "_circle" "3199.0625,383.5939" "0.075")
(command "_circle" "3199.0625,383.8939" "0.075")
(command "_circle" "3199.0625,384.1939" "0.075")
(command "_circle" "3198.7625,382.9939" "0.075")
(command "_circle" "3198.7625,383.2939" "0.075")
(command "_circle" "3198.7625,383.5939" "0.075")
(command "_circle" "3198.7625,383.8939" "0.075")
(command "_circle" "3198.7625,384.1939" "0.075")
(command "_circle" "3198.4625,382.9939" "0.075")
(command "_circle" "3198.4625,383.2939" "0.075")
(command "_circle" "3198.4625,383.5939" "0.075")
(command "_circle" "3198.4625,383.8939" "0.075")
(command "_circle" "3198.4625,384.1939" "0.075")
(command "_circle" "3198.1625,382.9939" "0.075")
(command "_circle" "3198.1625,383.2939" "0.075")
(command "_circle" "3198.1625,383.5939" "0.075")
(command "_circle" "3198.1625,383.8939" "0.075")
(command "_circle" "3198.1625,384.1939" "0.075")
(command "_circle" "3197.8625,382.9939" "0.075")
(command "_circle" "3197.8625,383.2939" "0.075")
(command "_circle" "3197.8625,383.5939" "0.075")
(command "_circle" "3197.8625,383.8939" "0.075")
(command "_circle" "3197.8625,384.1939" "0.075")
(command "_layer" "set" "nitride" "")
(setq coords (list 
(list 3200.2625 408.4369) 
(list 3200.2625 524.0816) 
(list 3199.7375 524.0816) 
(list 3199.7375 408.4369)))
(apply 'command (append '("pline") coords '("c")))
(setq currobj (ssadd (entlast) currobj))
(command "_layer" "set" "prebias" "")
(command "_rectangle" "3199.7375,408.4369" "3200.2625,524.0816")
(setq currobj (ssadd (entlast) currobj))
(command "_layer" "set" "nitride" "")
(setq coords (list 
(list 3200.2625 524.0816) 
(list 3200.5625 534.0816) 
(list 3200.5625 534.0816) 
(list 3200.5625 535.0816) 
(list 3274.585 534.3316) 
(list 3274.585 539.2746) 
(list 3200.5625 538.5246) 
(list 3200.5625 539.5246) 
(list 3200.5625 539.5246) 
(list 3200.2625 549.5246) 
(list 3199.7375 549.5246) 
(list 3199.4375 539.5246) 
(list 3199.4375 539.5246) 
(list 3199.4375 538.5246) 
(list 3125.415 539.2746) 
(list 3125.415 534.3316) 
(list 3199.4375 535.0816) 
(list 3199.4375 534.0816) 
(list 3199.4375 534.0816) 
(list 3199.7375 524.0816)))
(apply 'command (append '("pline") coords '("c")))
(setq currobj (ssadd (entlast) currobj))
(command "_layer" "set" "prebias" "")
(setq coords (list 
(list 3199.4375 524.0816) 
(list 3199.4375 535.0816) 
(list 3125.415 534.3316) 
(list 3125.415 539.2746) 
(list 3199.4375 538.5246) 
(list 3199.4375 549.5246) 
(list 3200.5625 549.5246) 
(list 3200.5625 538.5246) 
(list 3274.585 539.2746) 
(list 3274.585 534.3316) 
(list 3200.5625 535.0816) 
(list 3200.5625 524.0816)))
(apply 'command (append '("pline") coords '("c")))
(setq currobj (ssadd (entlast) currobj))
(command "_layer" "set" "nitride" "")
(command "_layer" "set" "fda1" "")
(setq coords (list 
(list 3200.5625 535.2246) 
(list 3274.585 534.4746) 
(list 3274.585 534.6516) 
(list 3200.5625 535.3016)))
(apply 'command (append '("pline") coords '("c")))
(setq currobj (ssadd (entlast) currobj))
(setq coords (list 
(list 3200.5625 535.4446) 
(list 3274.585 534.7946) 
(list 3274.585 534.9716) 
(list 3200.5625 535.5216)))
(apply 'command (append '("pline") coords '("c")))
(setq currobj (ssadd (entlast) currobj))
(setq coords (list 
(list 3200.5625 535.6646) 
(list 3274.585 535.1146) 
(list 3274.585 535.2916) 
(list 3200.5625 535.7416)))
(apply 'command (append '("pline") coords '("c")))
(setq currobj (ssadd (entlast) currobj))
(setq coords (list 
(list 3200.5625 535.8846) 
(list 3274.585 535.4346) 
(list 3274.585 535.6116) 
(list 3200.5625 535.9616)))
(apply 'command (append '("pline") coords '("c")))
(setq currobj (ssadd (entlast) currobj))
(setq coords (list 
(list 3200.5625 536.1046) 
(list 3274.585 535.7546) 
(list 3274.585 535.9316) 
(list 3200.5625 536.1816)))
(apply 'command (append '("pline") coords '("c")))
(setq currobj (ssadd (entlast) currobj))
(setq coords (list 
(list 3200.5625 536.3246) 
(list 3274.585 536.0746) 
(list 3274.585 536.2516) 
(list 3200.5625 536.4016)))
(apply 'command (append '("pline") coords '("c")))
(setq currobj (ssadd (entlast) currobj))
(setq coords (list 
(list 3200.5625 536.5446) 
(list 3274.585 536.3946) 
(list 3274.585 536.5716) 
(list 3200.5625 536.6216)))
(apply 'command (append '("pline") coords '("c")))
(setq currobj (ssadd (entlast) currobj))
(setq coords (list 
(list 3200.5625 536.7646) 
(list 3274.585 536.7146) 
(list 3274.585 536.8916) 
(list 3200.5625 536.8416)))
(apply 'command (append '("pline") coords '("c")))
(setq currobj (ssadd (entlast) currobj))
(setq coords (list 
(list 3200.5625 536.9846) 
(list 3274.585 537.0346) 
(list 3274.585 537.2116) 
(list 3200.5625 537.0616)))
(apply 'command (append '("pline") coords '("c")))
(setq currobj (ssadd (entlast) currobj))
(setq coords (list 
(list 3200.5625 537.2046) 
(list 3274.585 537.3546) 
(list 3274.585 537.5316) 
(list 3200.5625 537.2816)))
(apply 'command (append '("pline") coords '("c")))
(setq currobj (ssadd (entlast) currobj))
(setq coords (list 
(list 3200.5625 537.4246) 
(list 3274.585 537.6746) 
(list 3274.585 537.8516) 
(list 3200.5625 537.5016)))
(apply 'command (append '("pline") coords '("c")))
(setq currobj (ssadd (entlast) currobj))
(setq coords (list 
(list 3200.5625 537.6446) 
(list 3274.585 537.9946) 
(list 3274.585 538.1716) 
(list 3200.5625 537.7216)))
(apply 'command (append '("pline") coords '("c")))
(setq currobj (ssadd (entlast) currobj))
(setq coords (list 
(list 3200.5625 537.8646) 
(list 3274.585 538.3146) 
(list 3274.585 538.4916) 
(list 3200.5625 537.9416)))
(apply 'command (append '("pline") coords '("c")))
(setq currobj (ssadd (entlast) currobj))
(setq coords (list 
(list 3200.5625 538.0846) 
(list 3274.585 538.6346) 
(list 3274.585 538.8116) 
(list 3200.5625 538.1616)))
(apply 'command (append '("pline") coords '("c")))
(setq currobj (ssadd (entlast) currobj))
(setq coords (list 
(list 3200.5625 538.3046) 
(list 3274.585 538.9546) 
(list 3274.585 539.1316) 
(list 3200.5625 538.3816)))
(apply 'command (append '("pline") coords '("c")))
(setq currobj (ssadd (entlast) currobj))
(setq coords (list 
(list 3199.4375 538.3816) 
(list 3125.415 539.1316) 
(list 3125.415 538.9546) 
(list 3199.4375 538.3046)))
(apply 'command (append '("pline") coords '("c")))
(setq currobj (ssadd (entlast) currobj))
(setq coords (list 
(list 3199.4375 538.1616) 
(list 3125.415 538.8116) 
(list 3125.415 538.6346) 
(list 3199.4375 538.0846)))
(apply 'command (append '("pline") coords '("c")))
(setq currobj (ssadd (entlast) currobj))
(setq coords (list 
(list 3199.4375 537.9416) 
(list 3125.415 538.4916) 
(list 3125.415 538.3146) 
(list 3199.4375 537.8646)))
(apply 'command (append '("pline") coords '("c")))
(setq currobj (ssadd (entlast) currobj))
(setq coords (list 
(list 3199.4375 537.7216) 
(list 3125.415 538.1716) 
(list 3125.415 537.9946) 
(list 3199.4375 537.6446)))
(apply 'command (append '("pline") coords '("c")))
(setq currobj (ssadd (entlast) currobj))
(setq coords (list 
(list 3199.4375 537.5016) 
(list 3125.415 537.8516) 
(list 3125.415 537.6746) 
(list 3199.4375 537.4246)))
(apply 'command (append '("pline") coords '("c")))
(setq currobj (ssadd (entlast) currobj))
(setq coords (list 
(list 3199.4375 537.2816) 
(list 3125.415 537.5316) 
(list 3125.415 537.3546) 
(list 3199.4375 537.2046)))
(apply 'command (append '("pline") coords '("c")))
(setq currobj (ssadd (entlast) currobj))
(setq coords (list 
(list 3199.4375 537.0616) 
(list 3125.415 537.2116) 
(list 3125.415 537.0346) 
(list 3199.4375 536.9846)))
(apply 'command (append '("pline") coords '("c")))
(setq currobj (ssadd (entlast) currobj))
(setq coords (list 
(list 3199.4375 536.8416) 
(list 3125.415 536.8916) 
(list 3125.415 536.7146) 
(list 3199.4375 536.7646)))
(apply 'command (append '("pline") coords '("c")))
(setq currobj (ssadd (entlast) currobj))
(setq coords (list 
(list 3199.4375 536.6216) 
(list 3125.415 536.5716) 
(list 3125.415 536.3946) 
(list 3199.4375 536.5446)))
(apply 'command (append '("pline") coords '("c")))
(setq currobj (ssadd (entlast) currobj))
(setq coords (list 
(list 3199.4375 536.4016) 
(list 3125.415 536.2516) 
(list 3125.415 536.0746) 
(list 3199.4375 536.3246)))
(apply 'command (append '("pline") coords '("c")))
(setq currobj (ssadd (entlast) currobj))
(setq coords (list 
(list 3199.4375 536.1816) 
(list 3125.415 535.9316) 
(list 3125.415 535.7546) 
(list 3199.4375 536.1046)))
(apply 'command (append '("pline") coords '("c")))
(setq currobj (ssadd (entlast) currobj))
(setq coords (list 
(list 3199.4375 535.9616) 
(list 3125.415 535.6116) 
(list 3125.415 535.4346) 
(list 3199.4375 535.8846)))
(apply 'command (append '("pline") coords '("c")))
(setq currobj (ssadd (entlast) currobj))
(setq coords (list 
(list 3199.4375 535.7416) 
(list 3125.415 535.2916) 
(list 3125.415 535.1146) 
(list 3199.4375 535.6646)))
(apply 'command (append '("pline") coords '("c")))
(setq currobj (ssadd (entlast) currobj))
(setq coords (list 
(list 3199.4375 535.5216) 
(list 3125.415 534.9716) 
(list 3125.415 534.7946) 
(list 3199.4375 535.4446)))
(apply 'command (append '("pline") coords '("c")))
(setq currobj (ssadd (entlast) currobj))
(setq coords (list 
(list 3199.4375 535.3016) 
(list 3125.415 534.6516) 
(list 3125.415 534.4746) 
(list 3199.4375 535.2246)))
(apply 'command (append '("pline") coords '("c")))
(setq currobj (ssadd (entlast) currobj))
(command "_layer" "set" "nitride" "")
(command "_layer" "set" "text" "")
(command "_circle" "3199.0625,524.0816" "0.075")
(command "_circle" "3199.0625,524.3816" "0.075")
(command "_circle" "3199.0625,524.6816" "0.075")
(command "_circle" "3199.0625,524.9816" "0.075")
(command "_circle" "3199.0625,525.2816" "0.075")
(command "_circle" "3198.7625,524.0816" "0.075")
(command "_circle" "3198.7625,524.3816" "0.075")
(command "_circle" "3198.7625,524.6816" "0.075")
(command "_circle" "3198.7625,524.9816" "0.075")
(command "_circle" "3198.7625,525.2816" "0.075")
(command "_circle" "3198.4625,524.0816" "0.075")
(command "_circle" "3198.4625,524.3816" "0.075")
(command "_circle" "3198.4625,524.6816" "0.075")
(command "_circle" "3198.4625,524.9816" "0.075")
(command "_circle" "3198.4625,525.2816" "0.075")
(command "_circle" "3198.1625,524.0816" "0.075")
(command "_circle" "3198.1625,524.3816" "0.075")
(command "_circle" "3198.1625,524.6816" "0.075")
(command "_circle" "3198.1625,524.9816" "0.075")
(command "_circle" "3198.1625,525.2816" "0.075")
(command "_circle" "3197.8625,524.0816" "0.075")
(command "_circle" "3197.8625,524.3816" "0.075")
(command "_circle" "3197.8625,524.6816" "0.075")
(command "_circle" "3197.8625,524.9816" "0.075")
(command "_circle" "3197.8625,525.2816" "0.075")
(command "_layer" "set" "nitride" "")
(setq coords (list 
(list 3200.2625 549.5246) 
(list 3200.2625 665.1693) 
(list 3199.7375 665.1693) 
(list 3199.7375 549.5246)))
(apply 'command (append '("pline") coords '("c")))
(setq currobj (ssadd (entlast) currobj))
(command "_layer" "set" "prebias" "")
(command "_rectangle" "3199.7375,549.5246" "3200.2625,665.1693")
(setq currobj (ssadd (entlast) currobj))
(command "_layer" "set" "nitride" "")
(setq coords (list 
(list 3200.2625 665.1693) 
(list 3200.5625 675.1693) 
(list 3200.5625 675.1693) 
(list 3200.5625 676.1693) 
(list 3274.585 675.4193) 
(list 3274.585 680.3623) 
(list 3200.5625 679.6123) 
(list 3200.5625 680.6123) 
(list 3200.5625 680.6123) 
(list 3200.2625 690.6123) 
(list 3199.7375 690.6123) 
(list 3199.4375 680.6123) 
(list 3199.4375 680.6123) 
(list 3199.4375 679.6123) 
(list 3125.415 680.3623) 
(list 3125.415 675.4193) 
(list 3199.4375 676.1693) 
(list 3199.4375 675.1693) 
(list 3199.4375 675.1693) 
(list 3199.7375 665.1693)))
(apply 'command (append '("pline") coords '("c")))
(setq currobj (ssadd (entlast) currobj))
(command "_layer" "set" "prebias" "")
(setq coords (list 
(list 3199.4375 665.1693) 
(list 3199.4375 676.1693) 
(list 3125.415 675.4193) 
(list 3125.415 680.3623) 
(list 3199.4375 679.6123) 
(list 3199.4375 690.6123) 
(list 3200.5625 690.6123) 
(list 3200.5625 679.6123) 
(list 3274.585 680.3623) 
(list 3274.585 675.4193) 
(list 3200.5625 676.1693) 
(list 3200.5625 665.1693)))
(apply 'command (append '("pline") coords '("c")))
(setq currobj (ssadd (entlast) currobj))
(command "_layer" "set" "nitride" "")
(command "_layer" "set" "fda1" "")
(setq coords (list 
(list 3200.5625 676.3123) 
(list 3274.585 675.5623) 
(list 3274.585 675.7393) 
(list 3200.5625 676.3893)))
(apply 'command (append '("pline") coords '("c")))
(setq currobj (ssadd (entlast) currobj))
(setq coords (list 
(list 3200.5625 676.5323) 
(list 3274.585 675.8823) 
(list 3274.585 676.0593) 
(list 3200.5625 676.6093)))
(apply 'command (append '("pline") coords '("c")))
(setq currobj (ssadd (entlast) currobj))
(setq coords (list 
(list 3200.5625 676.7523) 
(list 3274.585 676.2023) 
(list 3274.585 676.3793) 
(list 3200.5625 676.8293)))
(apply 'command (append '("pline") coords '("c")))
(setq currobj (ssadd (entlast) currobj))
(setq coords (list 
(list 3200.5625 676.9723) 
(list 3274.585 676.5223) 
(list 3274.585 676.6993) 
(list 3200.5625 677.0493)))
(apply 'command (append '("pline") coords '("c")))
(setq currobj (ssadd (entlast) currobj))
(setq coords (list 
(list 3200.5625 677.1923) 
(list 3274.585 676.8423) 
(list 3274.585 677.0193) 
(list 3200.5625 677.2693)))
(apply 'command (append '("pline") coords '("c")))
(setq currobj (ssadd (entlast) currobj))
(setq coords (list 
(list 3200.5625 677.4123) 
(list 3274.585 677.1623) 
(list 3274.585 677.3393) 
(list 3200.5625 677.4893)))
(apply 'command (append '("pline") coords '("c")))
(setq currobj (ssadd (entlast) currobj))
(setq coords (list 
(list 3200.5625 677.6323) 
(list 3274.585 677.4823) 
(list 3274.585 677.6593) 
(list 3200.5625 677.7093)))
(apply 'command (append '("pline") coords '("c")))
(setq currobj (ssadd (entlast) currobj))
(setq coords (list 
(list 3200.5625 677.8523) 
(list 3274.585 677.8023) 
(list 3274.585 677.9793) 
(list 3200.5625 677.9293)))
(apply 'command (append '("pline") coords '("c")))
(setq currobj (ssadd (entlast) currobj))
(setq coords (list 
(list 3200.5625 678.0723) 
(list 3274.585 678.1223) 
(list 3274.585 678.2993) 
(list 3200.5625 678.1493)))
(apply 'command (append '("pline") coords '("c")))
(setq currobj (ssadd (entlast) currobj))
(setq coords (list 
(list 3200.5625 678.2923) 
(list 3274.585 678.4423) 
(list 3274.585 678.6193) 
(list 3200.5625 678.3693)))
(apply 'command (append '("pline") coords '("c")))
(setq currobj (ssadd (entlast) currobj))
(setq coords (list 
(list 3200.5625 678.5123) 
(list 3274.585 678.7623) 
(list 3274.585 678.9393) 
(list 3200.5625 678.5893)))
(apply 'command (append '("pline") coords '("c")))
(setq currobj (ssadd (entlast) currobj))
(setq coords (list 
(list 3200.5625 678.7323) 
(list 3274.585 679.0823) 
(list 3274.585 679.2593) 
(list 3200.5625 678.8093)))
(apply 'command (append '("pline") coords '("c")))
(setq currobj (ssadd (entlast) currobj))
(setq coords (list 
(list 3200.5625 678.9523) 
(list 3274.585 679.4023) 
(list 3274.585 679.5793) 
(list 3200.5625 679.0293)))
(apply 'command (append '("pline") coords '("c")))
(setq currobj (ssadd (entlast) currobj))
(setq coords (list 
(list 3200.5625 679.1723) 
(list 3274.585 679.7223) 
(list 3274.585 679.8993) 
(list 3200.5625 679.2493)))
(apply 'command (append '("pline") coords '("c")))
(setq currobj (ssadd (entlast) currobj))
(setq coords (list 
(list 3200.5625 679.3923) 
(list 3274.585 680.0423) 
(list 3274.585 680.2193) 
(list 3200.5625 679.4693)))
(apply 'command (append '("pline") coords '("c")))
(setq currobj (ssadd (entlast) currobj))
(setq coords (list 
(list 3199.4375 679.4693) 
(list 3125.415 680.2193) 
(list 3125.415 680.0423) 
(list 3199.4375 679.3923)))
(apply 'command (append '("pline") coords '("c")))
(setq currobj (ssadd (entlast) currobj))
(setq coords (list 
(list 3199.4375 679.2493) 
(list 3125.415 679.8993) 
(list 3125.415 679.7223) 
(list 3199.4375 679.1723)))
(apply 'command (append '("pline") coords '("c")))
(setq currobj (ssadd (entlast) currobj))
(setq coords (list 
(list 3199.4375 679.0293) 
(list 3125.415 679.5793) 
(list 3125.415 679.4023) 
(list 3199.4375 678.9523)))
(apply 'command (append '("pline") coords '("c")))
(setq currobj (ssadd (entlast) currobj))
(setq coords (list 
(list 3199.4375 678.8093) 
(list 3125.415 679.2593) 
(list 3125.415 679.0823) 
(list 3199.4375 678.7323)))
(apply 'command (append '("pline") coords '("c")))
(setq currobj (ssadd (entlast) currobj))
(setq coords (list 
(list 3199.4375 678.5893) 
(list 3125.415 678.9393) 
(list 3125.415 678.7623) 
(list 3199.4375 678.5123)))
(apply 'command (append '("pline") coords '("c")))
(setq currobj (ssadd (entlast) currobj))
(setq coords (list 
(list 3199.4375 678.3693) 
(list 3125.415 678.6193) 
(list 3125.415 678.4423) 
(list 3199.4375 678.2923)))
(apply 'command (append '("pline") coords '("c")))
(setq currobj (ssadd (entlast) currobj))
(setq coords (list 
(list 3199.4375 678.1493) 
(list 3125.415 678.2993) 
(list 3125.415 678.1223) 
(list 3199.4375 678.0723)))
(apply 'command (append '("pline") coords '("c")))
(setq currobj (ssadd (entlast) currobj))
(setq coords (list 
(list 3199.4375 677.9293) 
(list 3125.415 677.9793) 
(list 3125.415 677.8023) 
(list 3199.4375 677.8523)))
(apply 'command (append '("pline") coords '("c")))
(setq currobj (ssadd (entlast) currobj))
(setq coords (list 
(list 3199.4375 677.7093) 
(list 3125.415 677.6593) 
(list 3125.415 677.4823) 
(list 3199.4375 677.6323)))
(apply 'command (append '("pline") coords '("c")))
(setq currobj (ssadd (entlast) currobj))
(setq coords (list 
(list 3199.4375 677.4893) 
(list 3125.415 677.3393) 
(list 3125.415 677.1623) 
(list 3199.4375 677.4123)))
(apply 'command (append '("pline") coords '("c")))
(setq currobj (ssadd (entlast) currobj))
(setq coords (list 
(list 3199.4375 677.2693) 
(list 3125.415 677.0193) 
(list 3125.415 676.8423) 
(list 3199.4375 677.1923)))
(apply 'command (append '("pline") coords '("c")))
(setq currobj (ssadd (entlast) currobj))
(setq coords (list 
(list 3199.4375 677.0493) 
(list 3125.415 676.6993) 
(list 3125.415 676.5223) 
(list 3199.4375 676.9723)))
(apply 'command (append '("pline") coords '("c")))
(setq currobj (ssadd (entlast) currobj))
(setq coords (list 
(list 3199.4375 676.8293) 
(list 3125.415 676.3793) 
(list 3125.415 676.2023) 
(list 3199.4375 676.7523)))
(apply 'command (append '("pline") coords '("c")))
(setq currobj (ssadd (entlast) currobj))
(setq coords (list 
(list 3199.4375 676.6093) 
(list 3125.415 676.0593) 
(list 3125.415 675.8823) 
(list 3199.4375 676.5323)))
(apply 'command (append '("pline") coords '("c")))
(setq currobj (ssadd (entlast) currobj))
(setq coords (list 
(list 3199.4375 676.3893) 
(list 3125.415 675.7393) 
(list 3125.415 675.5623) 
(list 3199.4375 676.3123)))
(apply 'command (append '("pline") coords '("c")))
(setq currobj (ssadd (entlast) currobj))
(command "_layer" "set" "nitride" "")
(command "_layer" "set" "text" "")
(command "_circle" "3199.0625,665.1693" "0.075")
(command "_circle" "3199.0625,665.4693" "0.075")
(command "_circle" "3199.0625,665.7693" "0.075")
(command "_circle" "3199.0625,666.0693" "0.075")
(command "_circle" "3199.0625,666.3693" "0.075")
(command "_circle" "3198.7625,665.1693" "0.075")
(command "_circle" "3198.7625,665.4693" "0.075")
(command "_circle" "3198.7625,665.7693" "0.075")
(command "_circle" "3198.7625,666.0693" "0.075")
(command "_circle" "3198.7625,666.3693" "0.075")
(command "_circle" "3198.4625,665.1693" "0.075")
(command "_circle" "3198.4625,665.4693" "0.075")
(command "_circle" "3198.4625,665.7693" "0.075")
(command "_circle" "3198.4625,666.0693" "0.075")
(command "_circle" "3198.4625,666.3693" "0.075")
(command "_circle" "3198.1625,665.1693" "0.075")
(command "_circle" "3198.1625,665.4693" "0.075")
(command "_circle" "3198.1625,665.7693" "0.075")
(command "_circle" "3198.1625,666.0693" "0.075")
(command "_circle" "3198.1625,666.3693" "0.075")
(command "_circle" "3197.8625,665.1693" "0.075")
(command "_circle" "3197.8625,665.4693" "0.075")
(command "_circle" "3197.8625,665.7693" "0.075")
(command "_circle" "3197.8625,666.0693" "0.075")
(command "_circle" "3197.8625,666.3693" "0.075")
(command "_layer" "set" "nitride" "")
(setq coords (list 
(list 3200.2625 690.6123) 
(list 3200.2625 806.257) 
(list 3199.7375 806.257) 
(list 3199.7375 690.6123)))
(apply 'command (append '("pline") coords '("c")))
(setq currobj (ssadd (entlast) currobj))
(command "_layer" "set" "prebias" "")
(command "_rectangle" "3199.7375,690.6123" "3200.2625,806.257")
(setq currobj (ssadd (entlast) currobj))
(command "_layer" "set" "nitride" "")
(setq coords (list 
(list 3200.2625 806.257) 
(list 3200.5625 816.257) 
(list 3200.5625 816.257) 
(list 3200.5625 817.257) 
(list 3274.585 816.507) 
(list 3274.585 821.45) 
(list 3200.5625 820.7) 
(list 3200.5625 821.7) 
(list 3200.5625 821.7) 
(list 3200.2625 831.7) 
(list 3199.7375 831.7) 
(list 3199.4375 821.7) 
(list 3199.4375 821.7) 
(list 3199.4375 820.7) 
(list 3125.415 821.45) 
(list 3125.415 816.507) 
(list 3199.4375 817.257) 
(list 3199.4375 816.257) 
(list 3199.4375 816.257) 
(list 3199.7375 806.257)))
(apply 'command (append '("pline") coords '("c")))
(setq currobj (ssadd (entlast) currobj))
(command "_layer" "set" "prebias" "")
(setq coords (list 
(list 3199.4375 806.257) 
(list 3199.4375 817.257) 
(list 3125.415 816.507) 
(list 3125.415 821.45) 
(list 3199.4375 820.7) 
(list 3199.4375 831.7) 
(list 3200.5625 831.7) 
(list 3200.5625 820.7) 
(list 3274.585 821.45) 
(list 3274.585 816.507) 
(list 3200.5625 817.257) 
(list 3200.5625 806.257)))
(apply 'command (append '("pline") coords '("c")))
(setq currobj (ssadd (entlast) currobj))
(command "_layer" "set" "nitride" "")
(command "_layer" "set" "fda1" "")
(setq coords (list 
(list 3200.5625 817.4) 
(list 3274.585 816.65) 
(list 3274.585 816.827) 
(list 3200.5625 817.477)))
(apply 'command (append '("pline") coords '("c")))
(setq currobj (ssadd (entlast) currobj))
(setq coords (list 
(list 3200.5625 817.62) 
(list 3274.585 816.97) 
(list 3274.585 817.147) 
(list 3200.5625 817.697)))
(apply 'command (append '("pline") coords '("c")))
(setq currobj (ssadd (entlast) currobj))
(setq coords (list 
(list 3200.5625 817.84) 
(list 3274.585 817.29) 
(list 3274.585 817.467) 
(list 3200.5625 817.917)))
(apply 'command (append '("pline") coords '("c")))
(setq currobj (ssadd (entlast) currobj))
(setq coords (list 
(list 3200.5625 818.06) 
(list 3274.585 817.61) 
(list 3274.585 817.787) 
(list 3200.5625 818.137)))
(apply 'command (append '("pline") coords '("c")))
(setq currobj (ssadd (entlast) currobj))
(setq coords (list 
(list 3200.5625 818.28) 
(list 3274.585 817.93) 
(list 3274.585 818.107) 
(list 3200.5625 818.357)))
(apply 'command (append '("pline") coords '("c")))
(setq currobj (ssadd (entlast) currobj))
(setq coords (list 
(list 3200.5625 818.5) 
(list 3274.585 818.25) 
(list 3274.585 818.427) 
(list 3200.5625 818.577)))
(apply 'command (append '("pline") coords '("c")))
(setq currobj (ssadd (entlast) currobj))
(setq coords (list 
(list 3200.5625 818.72) 
(list 3274.585 818.57) 
(list 3274.585 818.747) 
(list 3200.5625 818.797)))
(apply 'command (append '("pline") coords '("c")))
(setq currobj (ssadd (entlast) currobj))
(setq coords (list 
(list 3200.5625 818.94) 
(list 3274.585 818.89) 
(list 3274.585 819.067) 
(list 3200.5625 819.017)))
(apply 'command (append '("pline") coords '("c")))
(setq currobj (ssadd (entlast) currobj))
(setq coords (list 
(list 3200.5625 819.16) 
(list 3274.585 819.21) 
(list 3274.585 819.387) 
(list 3200.5625 819.237)))
(apply 'command (append '("pline") coords '("c")))
(setq currobj (ssadd (entlast) currobj))
(setq coords (list 
(list 3200.5625 819.38) 
(list 3274.585 819.53) 
(list 3274.585 819.707) 
(list 3200.5625 819.457)))
(apply 'command (append '("pline") coords '("c")))
(setq currobj (ssadd (entlast) currobj))
(setq coords (list 
(list 3200.5625 819.6) 
(list 3274.585 819.85) 
(list 3274.585 820.027) 
(list 3200.5625 819.677)))
(apply 'command (append '("pline") coords '("c")))
(setq currobj (ssadd (entlast) currobj))
(setq coords (list 
(list 3200.5625 819.82) 
(list 3274.585 820.17) 
(list 3274.585 820.347) 
(list 3200.5625 819.897)))
(apply 'command (append '("pline") coords '("c")))
(setq currobj (ssadd (entlast) currobj))
(setq coords (list 
(list 3200.5625 820.04) 
(list 3274.585 820.49) 
(list 3274.585 820.667) 
(list 3200.5625 820.117)))
(apply 'command (append '("pline") coords '("c")))
(setq currobj (ssadd (entlast) currobj))
(setq coords (list 
(list 3200.5625 820.26) 
(list 3274.585 820.81) 
(list 3274.585 820.987) 
(list 3200.5625 820.337)))
(apply 'command (append '("pline") coords '("c")))
(setq currobj (ssadd (entlast) currobj))
(setq coords (list 
(list 3200.5625 820.48) 
(list 3274.585 821.13) 
(list 3274.585 821.307) 
(list 3200.5625 820.557)))
(apply 'command (append '("pline") coords '("c")))
(setq currobj (ssadd (entlast) currobj))
(setq coords (list 
(list 3199.4375 820.557) 
(list 3125.415 821.307) 
(list 3125.415 821.13) 
(list 3199.4375 820.48)))
(apply 'command (append '("pline") coords '("c")))
(setq currobj (ssadd (entlast) currobj))
(setq coords (list 
(list 3199.4375 820.337) 
(list 3125.415 820.987) 
(list 3125.415 820.81) 
(list 3199.4375 820.26)))
(apply 'command (append '("pline") coords '("c")))
(setq currobj (ssadd (entlast) currobj))
(setq coords (list 
(list 3199.4375 820.117) 
(list 3125.415 820.667) 
(list 3125.415 820.49) 
(list 3199.4375 820.04)))
(apply 'command (append '("pline") coords '("c")))
(setq currobj (ssadd (entlast) currobj))
(setq coords (list 
(list 3199.4375 819.897) 
(list 3125.415 820.347) 
(list 3125.415 820.17) 
(list 3199.4375 819.82)))
(apply 'command (append '("pline") coords '("c")))
(setq currobj (ssadd (entlast) currobj))
(setq coords (list 
(list 3199.4375 819.677) 
(list 3125.415 820.027) 
(list 3125.415 819.85) 
(list 3199.4375 819.6)))
(apply 'command (append '("pline") coords '("c")))
(setq currobj (ssadd (entlast) currobj))
(setq coords (list 
(list 3199.4375 819.457) 
(list 3125.415 819.707) 
(list 3125.415 819.53) 
(list 3199.4375 819.38)))
(apply 'command (append '("pline") coords '("c")))
(setq currobj (ssadd (entlast) currobj))
(setq coords (list 
(list 3199.4375 819.237) 
(list 3125.415 819.387) 
(list 3125.415 819.21) 
(list 3199.4375 819.16)))
(apply 'command (append '("pline") coords '("c")))
(setq currobj (ssadd (entlast) currobj))
(setq coords (list 
(list 3199.4375 819.017) 
(list 3125.415 819.067) 
(list 3125.415 818.89) 
(list 3199.4375 818.94)))
(apply 'command (append '("pline") coords '("c")))
(setq currobj (ssadd (entlast) currobj))
(setq coords (list 
(list 3199.4375 818.797) 
(list 3125.415 818.747) 
(list 3125.415 818.57) 
(list 3199.4375 818.72)))
(apply 'command (append '("pline") coords '("c")))
(setq currobj (ssadd (entlast) currobj))
(setq coords (list 
(list 3199.4375 818.577) 
(list 3125.415 818.427) 
(list 3125.415 818.25) 
(list 3199.4375 818.5)))
(apply 'command (append '("pline") coords '("c")))
(setq currobj (ssadd (entlast) currobj))
(setq coords (list 
(list 3199.4375 818.357) 
(list 3125.415 818.107) 
(list 3125.415 817.93) 
(list 3199.4375 818.28)))
(apply 'command (append '("pline") coords '("c")))
(setq currobj (ssadd (entlast) currobj))
(setq coords (list 
(list 3199.4375 818.137) 
(list 3125.415 817.787) 
(list 3125.415 817.61) 
(list 3199.4375 818.06)))
(apply 'command (append '("pline") coords '("c")))
(setq currobj (ssadd (entlast) currobj))
(setq coords (list 
(list 3199.4375 817.917) 
(list 3125.415 817.467) 
(list 3125.415 817.29) 
(list 3199.4375 817.84)))
(apply 'command (append '("pline") coords '("c")))
(setq currobj (ssadd (entlast) currobj))
(setq coords (list 
(list 3199.4375 817.697) 
(list 3125.415 817.147) 
(list 3125.415 816.97) 
(list 3199.4375 817.62)))
(apply 'command (append '("pline") coords '("c")))
(setq currobj (ssadd (entlast) currobj))
(setq coords (list 
(list 3199.4375 817.477) 
(list 3125.415 816.827) 
(list 3125.415 816.65) 
(list 3199.4375 817.4)))
(apply 'command (append '("pline") coords '("c")))
(setq currobj (ssadd (entlast) currobj))
(command "_layer" "set" "nitride" "")
(command "_layer" "set" "text" "")
(command "_circle" "3199.0625,806.257" "0.075")
(command "_circle" "3199.0625,806.557" "0.075")
(command "_circle" "3199.0625,806.857" "0.075")
(command "_circle" "3199.0625,807.157" "0.075")
(command "_circle" "3199.0625,807.457" "0.075")
(command "_circle" "3198.7625,806.257" "0.075")
(command "_circle" "3198.7625,806.557" "0.075")
(command "_circle" "3198.7625,806.857" "0.075")
(command "_circle" "3198.7625,807.157" "0.075")
(command "_circle" "3198.7625,807.457" "0.075")
(command "_circle" "3198.4625,806.257" "0.075")
(command "_circle" "3198.4625,806.557" "0.075")
(command "_circle" "3198.4625,806.857" "0.075")
(command "_circle" "3198.4625,807.157" "0.075")
(command "_circle" "3198.4625,807.457" "0.075")
(command "_circle" "3198.1625,806.257" "0.075")
(command "_circle" "3198.1625,806.557" "0.075")
(command "_circle" "3198.1625,806.857" "0.075")
(command "_circle" "3198.1625,807.157" "0.075")
(command "_circle" "3198.1625,807.457" "0.075")
(command "_circle" "3197.8625,806.257" "0.075")
(command "_circle" "3197.8625,806.557" "0.075")
(command "_circle" "3197.8625,806.857" "0.075")
(command "_circle" "3197.8625,807.157" "0.075")
(command "_circle" "3197.8625,807.457" "0.075")
(command "_layer" "set" "nitride" "")
(setq coords (list 
(list 3200.2625 831.7) 
(list 3200.2625 836.7) 
(list 3199.7375 836.7) 
(list 3199.7375 831.7)))
(apply 'command (append '("pline") coords '("c")))
(setq currobj (ssadd (entlast) currobj))
(command "_layer" "set" "prebias" "")
(command "_rectangle" "3199.7375,831.7" "3200.2625,836.7")
(setq currobj (ssadd (entlast) currobj))
(command "_layer" "set" "nitride" "")
(setq cooledsinglenanobeam10 currobj)
(setq currobj nil)
(setq currobj (ssadd))
; DRAWING PHOTONIC CRYSTAL
(command "_layer" "set" "negYjunc" "")
(setq coords (list 
(list 3200.125 866.7) 
(list 3200 851.7) 
(list 3200 866.7)))
(apply 'command (append '("pline") coords '("c")))
(setq currobj (ssadd (entlast) currobj))
(setq coords (list 
(list 3200.2625 836.7) 
(list 3200.405 866.7) 
(list 3201.112 866.7) 
(list 3201.112 836.7)))
(apply 'command (append '("pline") coords '("c")))
(setq currobj (ssadd (entlast) currobj))
(setq coords (list 
(list 3199.875 866.7) 
(list 3200 851.7) 
(list 3200 866.7)))
(apply 'command (append '("pline") coords '("c")))
(setq currobj (ssadd (entlast) currobj))
(setq coords (list 
(list 3199.7375 836.7) 
(list 3199.595 866.7) 
(list 3198.888 866.7) 
(list 3198.888 836.7)))
(apply 'command (append '("pline") coords '("c")))
(setq currobj (ssadd (entlast) currobj))
(command "_layer" "set" "nitride" "")
(setq yjunction10 currobj)
(setq currobj nil)
(setq currobj (ssadd))
(setq tap10 nil)
(setq tap10 (ssadd))
(command "_layer" "set" "phc" "")
(setq coords (list 
(list 3200 866.7) 
(list 3200.125 866.7) 
(list 3200.125 866.7103) 
(list 3200.125 866.7206) 
(list 3200.125 866.7308) 
(list 3200.125 866.7411) 
(list 3200.125 866.7514) 
(list 3200.125 866.7617) 
(list 3200.125 866.7719) 
(list 3200.125 866.7822) 
(list 3200.125 866.7925) 
(list 3200.125 866.8028) 
(list 3200.125 866.8131) 
(list 3200.125 866.8233) 
(list 3200.125 866.8336) 
(list 3200.125 866.8439) 
(list 3200.125 866.8542) 
(list 3200.125 866.8644) 
(list 3200.125 866.8747) 
(list 3200.125 866.885) 
(list 3200.125 866.8953) 
(list 3200.125 866.9056) 
(list 3200.125 866.9158) 
(list 3200.125 866.9261) 
(list 3200.125 866.9364) 
(list 3200.125 866.9467) 
(list 3200.125 866.9569) 
(list 3200.125 866.9672) 
(list 3200.125 866.9775) 
(list 3200.125 866.9878) 
(list 3200.125 866.9981) 
(list 3200.125 867.0083) 
(list 3200.125 867.0186) 
(list 3200.125 867.0289) 
(list 3200.125 867.0392) 
(list 3200.125 867.0494) 
(list 3200.125 867.0597) 
(list 3200.125 867.07) 
(list 3200 867.07)))
(apply 'command (append '("pline") coords '("c")))
(setq tap10 (ssadd (entlast) tap10))
(command "_mirror" (entlast) "" "3200,900" "3200,901" "No")
(setq tap10 (ssadd (entlast) tap10))
(setq coords (list 
(list 3200.4151 866.7) 
(list 3200.405 866.7) 
(list 3200.4053 866.7103) 
(list 3200.4055 866.7206) 
(list 3200.4057 866.7308) 
(list 3200.4059 866.7411) 
(list 3200.406 866.7514) 
(list 3200.4059 866.7617) 
(list 3200.4058 866.7719) 
(list 3200.4056 866.7822) 
(list 3200.4053 866.7925) 
(list 3200.4049 866.8028) 
(list 3200.4045 866.8131) 
(list 3200.404 866.8233) 
(list 3200.4034 866.8336) 
(list 3200.4029 866.8439) 
(list 3200.4024 866.8542) 
(list 3200.4019 866.8644) 
(list 3200.4015 866.8747) 
(list 3200.4012 866.885) 
(list 3200.4011 866.8953) 
(list 3200.4011 866.9056) 
(list 3200.4013 866.9158) 
(list 3200.4017 866.9261) 
(list 3200.4022 866.9364) 
(list 3200.4029 866.9467) 
(list 3200.4038 866.9569) 
(list 3200.4048 866.9672) 
(list 3200.4059 866.9775) 
(list 3200.4072 866.9878) 
(list 3200.4084 866.9981) 
(list 3200.4097 867.0083) 
(list 3200.411 867.0186) 
(list 3200.4121 867.0289) 
(list 3200.4131 867.0392) 
(list 3200.414 867.0494) 
(list 3200.4147 867.0597) 
(list 3200.4151 867.07) 
(list 3200.4151 867.07)))
(apply 'command (append '("pline") coords '("c")))
(setq tap10 (ssadd (entlast) tap10))
(command "_mirror" (entlast) "" "3200,900" "3200,901" "No")
(setq tap10 (ssadd (entlast) tap10))
(setq coords (list 
(list 3201.112 866.7) 
(list 3200.4151 866.7) 
(list 3200.4151 866.7103) 
(list 3200.4151 866.7206) 
(list 3200.4151 866.7308) 
(list 3200.4151 866.7411) 
(list 3200.4151 866.7514) 
(list 3200.4151 866.7617) 
(list 3200.4151 866.7719) 
(list 3200.4151 866.7822) 
(list 3200.4151 866.7925) 
(list 3200.4151 866.8028) 
(list 3200.4151 866.8131) 
(list 3200.4151 866.8233) 
(list 3200.4151 866.8336) 
(list 3200.4151 866.8439) 
(list 3200.4151 866.8542) 
(list 3200.4151 866.8644) 
(list 3200.4151 866.8747) 
(list 3200.4151 866.885) 
(list 3200.4151 866.8953) 
(list 3200.4151 866.9056) 
(list 3200.4151 866.9158) 
(list 3200.4151 866.9261) 
(list 3200.4151 866.9364) 
(list 3200.4151 866.9467) 
(list 3200.4151 866.9569) 
(list 3200.4151 866.9672) 
(list 3200.4151 866.9775) 
(list 3200.4151 866.9878) 
(list 3200.4151 866.9981) 
(list 3200.4151 867.0083) 
(list 3200.4151 867.0186) 
(list 3200.4151 867.0289) 
(list 3200.4151 867.0392) 
(list 3200.4151 867.0494) 
(list 3200.4151 867.0597) 
(list 3200.4151 867.07) 
(list 3201.112 867.07)))
(apply 'command (append '("pline") coords '("c")))
(setq tap10 (ssadd (entlast) tap10))
(command "_mirror" (entlast) "" "3200,900" "3200,901" "No")
(setq tap10 (ssadd (entlast) tap10))
(setq coords (list 
(list 3200 867.07) 
(list 3200.125 867.07) 
(list 3200.125 867.0803) 
(list 3200.125 867.0906) 
(list 3200.125 867.1008) 
(list 3200.125 867.1111) 
(list 3200.125 867.1214) 
(list 3200.125 867.1317) 
(list 3200.125 867.1419) 
(list 3200.125 867.1522) 
(list 3200.125 867.1625) 
(list 3200.125 867.1728) 
(list 3200.125 867.1831) 
(list 3200.125 867.1933) 
(list 3200.125 867.2036) 
(list 3200.125 867.2139) 
(list 3200.125 867.2242) 
(list 3200.125 867.2344) 
(list 3200.125 867.2447) 
(list 3200.125 867.255) 
(list 3200.125 867.2653) 
(list 3200.125 867.2756) 
(list 3200.125 867.2858) 
(list 3200.125 867.2961) 
(list 3200.125 867.3064) 
(list 3200.125 867.3167) 
(list 3200.125 867.3269) 
(list 3200.125 867.3372) 
(list 3200.125 867.3475) 
(list 3200.125 867.3578) 
(list 3200.125 867.3681) 
(list 3200.125 867.3783) 
(list 3200.125 867.3886) 
(list 3200.125 867.3989) 
(list 3200.125 867.4092) 
(list 3200.125 867.4194) 
(list 3200.125 867.4297) 
(list 3200.125 867.44) 
(list 3200 867.44)))
(apply 'command (append '("pline") coords '("c")))
(setq tap10 (ssadd (entlast) tap10))
(command "_mirror" (entlast) "" "3200,900" "3200,901" "No")
(setq tap10 (ssadd (entlast) tap10))
(setq coords (list 
(list 3200.4251 867.07) 
(list 3200.4151 867.07) 
(list 3200.4152 867.0803) 
(list 3200.4151 867.0906) 
(list 3200.4146 867.1008) 
(list 3200.4139 867.1111) 
(list 3200.4129 867.1214) 
(list 3200.4116 867.1317) 
(list 3200.4101 867.1419) 
(list 3200.4084 867.1522) 
(list 3200.4066 867.1625) 
(list 3200.4047 867.1728) 
(list 3200.4027 867.1831) 
(list 3200.4008 867.1933) 
(list 3200.399 867.2036) 
(list 3200.3974 867.2139) 
(list 3200.396 867.2242) 
(list 3200.3949 867.2344) 
(list 3200.3941 867.2447) 
(list 3200.3937 867.255) 
(list 3200.3937 867.2653) 
(list 3200.3941 867.2756) 
(list 3200.3949 867.2858) 
(list 3200.3962 867.2961) 
(list 3200.3978 867.3064) 
(list 3200.3998 867.3167) 
(list 3200.402 867.3269) 
(list 3200.4046 867.3372) 
(list 3200.4072 867.3475) 
(list 3200.41 867.3578) 
(list 3200.4127 867.3681) 
(list 3200.4154 867.3783) 
(list 3200.4179 867.3886) 
(list 3200.4201 867.3989) 
(list 3200.422 867.4092) 
(list 3200.4235 867.4194) 
(list 3200.4246 867.4297) 
(list 3200.4251 867.44) 
(list 3200.4251 867.44)))
(apply 'command (append '("pline") coords '("c")))
(setq tap10 (ssadd (entlast) tap10))
(command "_mirror" (entlast) "" "3200,900" "3200,901" "No")
(setq tap10 (ssadd (entlast) tap10))
(setq coords (list 
(list 3201.112 867.07) 
(list 3200.4251 867.07) 
(list 3200.4251 867.0803) 
(list 3200.4251 867.0906) 
(list 3200.4251 867.1008) 
(list 3200.4251 867.1111) 
(list 3200.4251 867.1214) 
(list 3200.4251 867.1317) 
(list 3200.4251 867.1419) 
(list 3200.4251 867.1522) 
(list 3200.4251 867.1625) 
(list 3200.4251 867.1728) 
(list 3200.4251 867.1831) 
(list 3200.4251 867.1933) 
(list 3200.4251 867.2036) 
(list 3200.4251 867.2139) 
(list 3200.4251 867.2242) 
(list 3200.4251 867.2344) 
(list 3200.4251 867.2447) 
(list 3200.4251 867.255) 
(list 3200.4251 867.2653) 
(list 3200.4251 867.2756) 
(list 3200.4251 867.2858) 
(list 3200.4251 867.2961) 
(list 3200.4251 867.3064) 
(list 3200.4251 867.3167) 
(list 3200.4251 867.3269) 
(list 3200.4251 867.3372) 
(list 3200.4251 867.3475) 
(list 3200.4251 867.3578) 
(list 3200.4251 867.3681) 
(list 3200.4251 867.3783) 
(list 3200.4251 867.3886) 
(list 3200.4251 867.3989) 
(list 3200.4251 867.4092) 
(list 3200.4251 867.4194) 
(list 3200.4251 867.4297) 
(list 3200.4251 867.44) 
(list 3201.112 867.44)))
(apply 'command (append '("pline") coords '("c")))
(setq tap10 (ssadd (entlast) tap10))
(command "_mirror" (entlast) "" "3200,900" "3200,901" "No")
(setq tap10 (ssadd (entlast) tap10))
(setq coords (list 
(list 3200 867.44) 
(list 3200.125 867.44) 
(list 3200.125 867.4503) 
(list 3200.125 867.4606) 
(list 3200.125 867.4708) 
(list 3200.125 867.4811) 
(list 3200.125 867.4914) 
(list 3200.125 867.5017) 
(list 3200.125 867.5119) 
(list 3200.125 867.5222) 
(list 3200.125 867.5325) 
(list 3200.125 867.5428) 
(list 3200.125 867.5531) 
(list 3200.125 867.5633) 
(list 3200.125 867.5736) 
(list 3200.125 867.5839) 
(list 3200.125 867.5942) 
(list 3200.125 867.6044) 
(list 3200.125 867.6147) 
(list 3200.125 867.625) 
(list 3200.125 867.6353) 
(list 3200.125 867.6456) 
(list 3200.125 867.6558) 
(list 3200.125 867.6661) 
(list 3200.125 867.6764) 
(list 3200.125 867.6867) 
(list 3200.125 867.6969) 
(list 3200.125 867.7072) 
(list 3200.125 867.7175) 
(list 3200.125 867.7278) 
(list 3200.125 867.7381) 
(list 3200.125 867.7483) 
(list 3200.125 867.7586) 
(list 3200.125 867.7689) 
(list 3200.125 867.7792) 
(list 3200.125 867.7894) 
(list 3200.125 867.7997) 
(list 3200.125 867.81) 
(list 3200 867.81)))
(apply 'command (append '("pline") coords '("c")))
(setq tap10 (ssadd (entlast) tap10))
(command "_mirror" (entlast) "" "3200,900" "3200,901" "No")
(setq tap10 (ssadd (entlast) tap10))
(setq coords (list 
(list 3200.4352 867.44) 
(list 3200.4251 867.44) 
(list 3200.4251 867.4503) 
(list 3200.4246 867.4606) 
(list 3200.4235 867.4708) 
(list 3200.4219 867.4811) 
(list 3200.4198 867.4914) 
(list 3200.4173 867.5017) 
(list 3200.4144 867.5119) 
(list 3200.4112 867.5222) 
(list 3200.4079 867.5325) 
(list 3200.4044 867.5428) 
(list 3200.401 867.5531) 
(list 3200.3977 867.5633) 
(list 3200.3946 867.5736) 
(list 3200.3919 867.5839) 
(list 3200.3896 867.5942) 
(list 3200.3879 867.6044) 
(list 3200.3867 867.6147) 
(list 3200.3862 867.625) 
(list 3200.3863 867.6353) 
(list 3200.3871 867.6456) 
(list 3200.3886 867.6558) 
(list 3200.3907 867.6661) 
(list 3200.3934 867.6764) 
(list 3200.3966 867.6867) 
(list 3200.4003 867.6969) 
(list 3200.4043 867.7072) 
(list 3200.4085 867.7175) 
(list 3200.4128 867.7278) 
(list 3200.417 867.7381) 
(list 3200.4211 867.7483) 
(list 3200.4248 867.7586) 
(list 3200.4281 867.7689) 
(list 3200.4309 867.7792) 
(list 3200.4331 867.7894) 
(list 3200.4345 867.7997) 
(list 3200.4352 867.81) 
(list 3200.4352 867.81)))
(apply 'command (append '("pline") coords '("c")))
(setq tap10 (ssadd (entlast) tap10))
(command "_mirror" (entlast) "" "3200,900" "3200,901" "No")
(setq tap10 (ssadd (entlast) tap10))
(setq coords (list 
(list 3201.112 867.44) 
(list 3200.4352 867.44) 
(list 3200.4352 867.4503) 
(list 3200.4352 867.4606) 
(list 3200.4352 867.4708) 
(list 3200.4352 867.4811) 
(list 3200.4352 867.4914) 
(list 3200.4352 867.5017) 
(list 3200.4352 867.5119) 
(list 3200.4352 867.5222) 
(list 3200.4352 867.5325) 
(list 3200.4352 867.5428) 
(list 3200.4352 867.5531) 
(list 3200.4352 867.5633) 
(list 3200.4352 867.5736) 
(list 3200.4352 867.5839) 
(list 3200.4352 867.5942) 
(list 3200.4352 867.6044) 
(list 3200.4352 867.6147) 
(list 3200.4352 867.625) 
(list 3200.4352 867.6353) 
(list 3200.4352 867.6456) 
(list 3200.4352 867.6558) 
(list 3200.4352 867.6661) 
(list 3200.4352 867.6764) 
(list 3200.4352 867.6867) 
(list 3200.4352 867.6969) 
(list 3200.4352 867.7072) 
(list 3200.4352 867.7175) 
(list 3200.4352 867.7278) 
(list 3200.4352 867.7381) 
(list 3200.4352 867.7483) 
(list 3200.4352 867.7586) 
(list 3200.4352 867.7689) 
(list 3200.4352 867.7792) 
(list 3200.4352 867.7894) 
(list 3200.4352 867.7997) 
(list 3200.4352 867.81) 
(list 3201.112 867.81)))
(apply 'command (append '("pline") coords '("c")))
(setq tap10 (ssadd (entlast) tap10))
(command "_mirror" (entlast) "" "3200,900" "3200,901" "No")
(setq tap10 (ssadd (entlast) tap10))
(setq coords (list 
(list 3200 867.81) 
(list 3200.125 867.81) 
(list 3200.125 867.8203) 
(list 3200.125 867.8306) 
(list 3200.125 867.8408) 
(list 3200.125 867.8511) 
(list 3200.125 867.8614) 
(list 3200.125 867.8717) 
(list 3200.125 867.8819) 
(list 3200.125 867.8922) 
(list 3200.125 867.9025) 
(list 3200.125 867.9128) 
(list 3200.125 867.9231) 
(list 3200.125 867.9333) 
(list 3200.125 867.9436) 
(list 3200.125 867.9539) 
(list 3200.125 867.9642) 
(list 3200.125 867.9744) 
(list 3200.125 867.9847) 
(list 3200.125 867.995) 
(list 3200.125 868.0053) 
(list 3200.125 868.0156) 
(list 3200.125 868.0258) 
(list 3200.125 868.0361) 
(list 3200.125 868.0464) 
(list 3200.125 868.0567) 
(list 3200.125 868.0669) 
(list 3200.125 868.0772) 
(list 3200.125 868.0875) 
(list 3200.125 868.0978) 
(list 3200.125 868.1081) 
(list 3200.125 868.1183) 
(list 3200.125 868.1286) 
(list 3200.125 868.1389) 
(list 3200.125 868.1492) 
(list 3200.125 868.1594) 
(list 3200.125 868.1697) 
(list 3200.125 868.18) 
(list 3200 868.18)))
(apply 'command (append '("pline") coords '("c")))
(setq tap10 (ssadd (entlast) tap10))
(command "_mirror" (entlast) "" "3200,900" "3200,901" "No")
(setq tap10 (ssadd (entlast) tap10))
(setq coords (list 
(list 3200.4453 867.81) 
(list 3200.4352 867.81) 
(list 3200.4351 867.8203) 
(list 3200.4341 867.8306) 
(list 3200.4324 867.8408) 
(list 3200.4299 867.8511) 
(list 3200.4267 867.8614) 
(list 3200.4229 867.8717) 
(list 3200.4187 867.8819) 
(list 3200.414 867.8922) 
(list 3200.4091 867.9025) 
(list 3200.4041 867.9128) 
(list 3200.3992 867.9231) 
(list 3200.3946 867.9333) 
(list 3200.3902 867.9436) 
(list 3200.3864 867.9539) 
(list 3200.3833 867.9642) 
(list 3200.3809 867.9744) 
(list 3200.3793 867.9847) 
(list 3200.3786 867.995) 
(list 3200.3789 868.0053) 
(list 3200.3801 868.0156) 
(list 3200.3822 868.0258) 
(list 3200.3852 868.0361) 
(list 3200.389 868.0464) 
(list 3200.3935 868.0567) 
(list 3200.3986 868.0669) 
(list 3200.404 868.0772) 
(list 3200.4097 868.0875) 
(list 3200.4156 868.0978) 
(list 3200.4213 868.1081) 
(list 3200.4267 868.1183) 
(list 3200.4317 868.1286) 
(list 3200.4361 868.1389) 
(list 3200.4398 868.1492) 
(list 3200.4426 868.1594) 
(list 3200.4445 868.1697) 
(list 3200.4453 868.18) 
(list 3200.4453 868.18)))
(apply 'command (append '("pline") coords '("c")))
(setq tap10 (ssadd (entlast) tap10))
(command "_mirror" (entlast) "" "3200,900" "3200,901" "No")
(setq tap10 (ssadd (entlast) tap10))
(setq coords (list 
(list 3201.112 867.81) 
(list 3200.4453 867.81) 
(list 3200.4453 867.8203) 
(list 3200.4453 867.8306) 
(list 3200.4453 867.8408) 
(list 3200.4453 867.8511) 
(list 3200.4453 867.8614) 
(list 3200.4453 867.8717) 
(list 3200.4453 867.8819) 
(list 3200.4453 867.8922) 
(list 3200.4453 867.9025) 
(list 3200.4453 867.9128) 
(list 3200.4453 867.9231) 
(list 3200.4453 867.9333) 
(list 3200.4453 867.9436) 
(list 3200.4453 867.9539) 
(list 3200.4453 867.9642) 
(list 3200.4453 867.9744) 
(list 3200.4453 867.9847) 
(list 3200.4453 867.995) 
(list 3200.4453 868.0053) 
(list 3200.4453 868.0156) 
(list 3200.4453 868.0258) 
(list 3200.4453 868.0361) 
(list 3200.4453 868.0464) 
(list 3200.4453 868.0567) 
(list 3200.4453 868.0669) 
(list 3200.4453 868.0772) 
(list 3200.4453 868.0875) 
(list 3200.4453 868.0978) 
(list 3200.4453 868.1081) 
(list 3200.4453 868.1183) 
(list 3200.4453 868.1286) 
(list 3200.4453 868.1389) 
(list 3200.4453 868.1492) 
(list 3200.4453 868.1594) 
(list 3200.4453 868.1697) 
(list 3200.4453 868.18) 
(list 3201.112 868.18)))
(apply 'command (append '("pline") coords '("c")))
(setq tap10 (ssadd (entlast) tap10))
(command "_mirror" (entlast) "" "3200,900" "3200,901" "No")
(setq tap10 (ssadd (entlast) tap10))
(setq coords (list 
(list 3200 868.18) 
(list 3200.125 868.18) 
(list 3200.125 868.1903) 
(list 3200.125 868.2006) 
(list 3200.125 868.2108) 
(list 3200.125 868.2211) 
(list 3200.125 868.2314) 
(list 3200.125 868.2417) 
(list 3200.125 868.2519) 
(list 3200.125 868.2622) 
(list 3200.125 868.2725) 
(list 3200.125 868.2828) 
(list 3200.125 868.2931) 
(list 3200.125 868.3033) 
(list 3200.125 868.3136) 
(list 3200.125 868.3239) 
(list 3200.125 868.3342) 
(list 3200.125 868.3444) 
(list 3200.125 868.3547) 
(list 3200.125 868.365) 
(list 3200.125 868.3753) 
(list 3200.125 868.3856) 
(list 3200.125 868.3958) 
(list 3200.125 868.4061) 
(list 3200.125 868.4164) 
(list 3200.125 868.4267) 
(list 3200.125 868.4369) 
(list 3200.125 868.4472) 
(list 3200.125 868.4575) 
(list 3200.125 868.4678) 
(list 3200.125 868.4781) 
(list 3200.125 868.4883) 
(list 3200.125 868.4986) 
(list 3200.125 868.5089) 
(list 3200.125 868.5192) 
(list 3200.125 868.5294) 
(list 3200.125 868.5397) 
(list 3200.125 868.55) 
(list 3200 868.55)))
(apply 'command (append '("pline") coords '("c")))
(setq tap10 (ssadd (entlast) tap10))
(command "_mirror" (entlast) "" "3200,900" "3200,901" "No")
(setq tap10 (ssadd (entlast) tap10))
(setq coords (list 
(list 3200.4553 868.18) 
(list 3200.4453 868.18) 
(list 3200.445 868.1903) 
(list 3200.4437 868.2006) 
(list 3200.4413 868.2108) 
(list 3200.4379 868.2211) 
(list 3200.4337 868.2314) 
(list 3200.4286 868.2417) 
(list 3200.4229 868.2519) 
(list 3200.4168 868.2622) 
(list 3200.4104 868.2725) 
(list 3200.4039 868.2828) 
(list 3200.3975 868.2931) 
(list 3200.3914 868.3033) 
(list 3200.3859 868.3136) 
(list 3200.381 868.3239) 
(list 3200.3769 868.3342) 
(list 3200.3739 868.3444) 
(list 3200.3719 868.3547) 
(list 3200.3711 868.365) 
(list 3200.3715 868.3753) 
(list 3200.3731 868.3856) 
(list 3200.3759 868.3958) 
(list 3200.3798 868.4061) 
(list 3200.3846 868.4164) 
(list 3200.3904 868.4267) 
(list 3200.3968 868.4369) 
(list 3200.4038 868.4472) 
(list 3200.411 868.4575) 
(list 3200.4184 868.4678) 
(list 3200.4256 868.4781) 
(list 3200.4324 868.4883) 
(list 3200.4387 868.4986) 
(list 3200.4441 868.5089) 
(list 3200.4487 868.5192) 
(list 3200.4522 868.5294) 
(list 3200.4544 868.5397) 
(list 3200.4553 868.55) 
(list 3200.4553 868.55)))
(apply 'command (append '("pline") coords '("c")))
(setq tap10 (ssadd (entlast) tap10))
(command "_mirror" (entlast) "" "3200,900" "3200,901" "No")
(setq tap10 (ssadd (entlast) tap10))
(setq coords (list 
(list 3201.112 868.18) 
(list 3200.4553 868.18) 
(list 3200.4553 868.1903) 
(list 3200.4553 868.2006) 
(list 3200.4553 868.2108) 
(list 3200.4553 868.2211) 
(list 3200.4553 868.2314) 
(list 3200.4553 868.2417) 
(list 3200.4553 868.2519) 
(list 3200.4553 868.2622) 
(list 3200.4553 868.2725) 
(list 3200.4553 868.2828) 
(list 3200.4553 868.2931) 
(list 3200.4553 868.3033) 
(list 3200.4553 868.3136) 
(list 3200.4553 868.3239) 
(list 3200.4553 868.3342) 
(list 3200.4553 868.3444) 
(list 3200.4553 868.3547) 
(list 3200.4553 868.365) 
(list 3200.4553 868.3753) 
(list 3200.4553 868.3856) 
(list 3200.4553 868.3958) 
(list 3200.4553 868.4061) 
(list 3200.4553 868.4164) 
(list 3200.4553 868.4267) 
(list 3200.4553 868.4369) 
(list 3200.4553 868.4472) 
(list 3200.4553 868.4575) 
(list 3200.4553 868.4678) 
(list 3200.4553 868.4781) 
(list 3200.4553 868.4883) 
(list 3200.4553 868.4986) 
(list 3200.4553 868.5089) 
(list 3200.4553 868.5192) 
(list 3200.4553 868.5294) 
(list 3200.4553 868.5397) 
(list 3200.4553 868.55) 
(list 3201.112 868.55)))
(apply 'command (append '("pline") coords '("c")))
(setq tap10 (ssadd (entlast) tap10))
(command "_mirror" (entlast) "" "3200,900" "3200,901" "No")
(setq tap10 (ssadd (entlast) tap10))
(setq coords (list 
(list 3200 868.55) 
(list 3200.125 868.55) 
(list 3200.125 868.5603) 
(list 3200.125 868.5706) 
(list 3200.125 868.5808) 
(list 3200.125 868.5911) 
(list 3200.125 868.6014) 
(list 3200.125 868.6117) 
(list 3200.125 868.6219) 
(list 3200.125 868.6322) 
(list 3200.125 868.6425) 
(list 3200.125 868.6528) 
(list 3200.125 868.6631) 
(list 3200.125 868.6733) 
(list 3200.125 868.6836) 
(list 3200.125 868.6939) 
(list 3200.125 868.7042) 
(list 3200.125 868.7144) 
(list 3200.125 868.7247) 
(list 3200.125 868.735) 
(list 3200.125 868.7453) 
(list 3200.125 868.7556) 
(list 3200.125 868.7658) 
(list 3200.125 868.7761) 
(list 3200.125 868.7864) 
(list 3200.125 868.7967) 
(list 3200.125 868.8069) 
(list 3200.125 868.8172) 
(list 3200.125 868.8275) 
(list 3200.125 868.8378) 
(list 3200.125 868.8481) 
(list 3200.125 868.8583) 
(list 3200.125 868.8686) 
(list 3200.125 868.8789) 
(list 3200.125 868.8892) 
(list 3200.125 868.8994) 
(list 3200.125 868.9097) 
(list 3200.125 868.92) 
(list 3200 868.92)))
(apply 'command (append '("pline") coords '("c")))
(setq tap10 (ssadd (entlast) tap10))
(command "_mirror" (entlast) "" "3200,900" "3200,901" "No")
(setq tap10 (ssadd (entlast) tap10))
(setq coords (list 
(list 3200.4654 868.55) 
(list 3200.4553 868.55) 
(list 3200.4549 868.5603) 
(list 3200.4532 868.5706) 
(list 3200.4502 868.5808) 
(list 3200.4459 868.5911) 
(list 3200.4406 868.6014) 
(list 3200.4343 868.6117) 
(list 3200.4272 868.6219) 
(list 3200.4196 868.6322) 
(list 3200.4117 868.6425) 
(list 3200.4036 868.6528) 
(list 3200.3958 868.6631) 
(list 3200.3883 868.6733) 
(list 3200.3815 868.6836) 
(list 3200.3755 868.6939) 
(list 3200.3706 868.7042) 
(list 3200.3669 868.7144) 
(list 3200.3645 868.7247) 
(list 3200.3636 868.735) 
(list 3200.3641 868.7453) 
(list 3200.3661 868.7556) 
(list 3200.3695 868.7658) 
(list 3200.3743 868.7761) 
(list 3200.3802 868.7864) 
(list 3200.3872 868.7967) 
(list 3200.3951 868.8069) 
(list 3200.4035 868.8172) 
(list 3200.4123 868.8275) 
(list 3200.4211 868.8378) 
(list 3200.4298 868.8481) 
(list 3200.4381 868.8583) 
(list 3200.4456 868.8686) 
(list 3200.4522 868.8789) 
(list 3200.4576 868.8892) 
(list 3200.4617 868.8994) 
(list 3200.4643 868.9097) 
(list 3200.4654 868.92) 
(list 3200.4654 868.92)))
(apply 'command (append '("pline") coords '("c")))
(setq tap10 (ssadd (entlast) tap10))
(command "_mirror" (entlast) "" "3200,900" "3200,901" "No")
(setq tap10 (ssadd (entlast) tap10))
(setq coords (list 
(list 3201.112 868.55) 
(list 3200.4654 868.55) 
(list 3200.4654 868.5603) 
(list 3200.4654 868.5706) 
(list 3200.4654 868.5808) 
(list 3200.4654 868.5911) 
(list 3200.4654 868.6014) 
(list 3200.4654 868.6117) 
(list 3200.4654 868.6219) 
(list 3200.4654 868.6322) 
(list 3200.4654 868.6425) 
(list 3200.4654 868.6528) 
(list 3200.4654 868.6631) 
(list 3200.4654 868.6733) 
(list 3200.4654 868.6836) 
(list 3200.4654 868.6939) 
(list 3200.4654 868.7042) 
(list 3200.4654 868.7144) 
(list 3200.4654 868.7247) 
(list 3200.4654 868.735) 
(list 3200.4654 868.7453) 
(list 3200.4654 868.7556) 
(list 3200.4654 868.7658) 
(list 3200.4654 868.7761) 
(list 3200.4654 868.7864) 
(list 3200.4654 868.7967) 
(list 3200.4654 868.8069) 
(list 3200.4654 868.8172) 
(list 3200.4654 868.8275) 
(list 3200.4654 868.8378) 
(list 3200.4654 868.8481) 
(list 3200.4654 868.8583) 
(list 3200.4654 868.8686) 
(list 3200.4654 868.8789) 
(list 3200.4654 868.8892) 
(list 3200.4654 868.8994) 
(list 3200.4654 868.9097) 
(list 3200.4654 868.92) 
(list 3201.112 868.92)))
(apply 'command (append '("pline") coords '("c")))
(setq tap10 (ssadd (entlast) tap10))
(command "_mirror" (entlast) "" "3200,900" "3200,901" "No")
(setq tap10 (ssadd (entlast) tap10))
(setq coords (list 
(list 3200 868.92) 
(list 3200.125 868.92) 
(list 3200.125 868.9303) 
(list 3200.125 868.9406) 
(list 3200.125 868.9508) 
(list 3200.125 868.9611) 
(list 3200.125 868.9714) 
(list 3200.125 868.9817) 
(list 3200.125 868.9919) 
(list 3200.125 869.0022) 
(list 3200.125 869.0125) 
(list 3200.125 869.0228) 
(list 3200.125 869.0331) 
(list 3200.125 869.0433) 
(list 3200.125 869.0536) 
(list 3200.125 869.0639) 
(list 3200.125 869.0742) 
(list 3200.125 869.0844) 
(list 3200.125 869.0947) 
(list 3200.125 869.105) 
(list 3200.125 869.1153) 
(list 3200.125 869.1256) 
(list 3200.125 869.1358) 
(list 3200.125 869.1461) 
(list 3200.125 869.1564) 
(list 3200.125 869.1667) 
(list 3200.125 869.1769) 
(list 3200.125 869.1872) 
(list 3200.125 869.1975) 
(list 3200.125 869.2078) 
(list 3200.125 869.2181) 
(list 3200.125 869.2283) 
(list 3200.125 869.2386) 
(list 3200.125 869.2489) 
(list 3200.125 869.2592) 
(list 3200.125 869.2694) 
(list 3200.125 869.2797) 
(list 3200.125 869.29) 
(list 3200 869.29)))
(apply 'command (append '("pline") coords '("c")))
(setq tap10 (ssadd (entlast) tap10))
(command "_mirror" (entlast) "" "3200,900" "3200,901" "No")
(setq tap10 (ssadd (entlast) tap10))
(setq coords (list 
(list 3200.4755 868.92) 
(list 3200.4654 868.92) 
(list 3200.4649 868.9303) 
(list 3200.4627 868.9406) 
(list 3200.4591 868.9508) 
(list 3200.4539 868.9611) 
(list 3200.4475 868.9714) 
(list 3200.4399 868.9817) 
(list 3200.4315 868.9919) 
(list 3200.4224 869.0022) 
(list 3200.4129 869.0125) 
(list 3200.4034 869.0228) 
(list 3200.394 869.0331) 
(list 3200.3852 869.0433) 
(list 3200.3771 869.0536) 
(list 3200.37 869.0639) 
(list 3200.3642 869.0742) 
(list 3200.3599 869.0844) 
(list 3200.3571 869.0947) 
(list 3200.356 869.105) 
(list 3200.3567 869.1153) 
(list 3200.3591 869.1256) 
(list 3200.3632 869.1358) 
(list 3200.3688 869.1461) 
(list 3200.3759 869.1564) 
(list 3200.3841 869.1667) 
(list 3200.3933 869.1769) 
(list 3200.4032 869.1872) 
(list 3200.4136 869.1975) 
(list 3200.4239 869.2078) 
(list 3200.4341 869.2181) 
(list 3200.4437 869.2283) 
(list 3200.4525 869.2386) 
(list 3200.4602 869.2489) 
(list 3200.4665 869.2592) 
(list 3200.4712 869.2694) 
(list 3200.4743 869.2797) 
(list 3200.4755 869.29) 
(list 3200.4755 869.29)))
(apply 'command (append '("pline") coords '("c")))
(setq tap10 (ssadd (entlast) tap10))
(command "_mirror" (entlast) "" "3200,900" "3200,901" "No")
(setq tap10 (ssadd (entlast) tap10))
(setq coords (list 
(list 3201.112 868.92) 
(list 3200.4755 868.92) 
(list 3200.4755 868.9303) 
(list 3200.4755 868.9406) 
(list 3200.4755 868.9508) 
(list 3200.4755 868.9611) 
(list 3200.4755 868.9714) 
(list 3200.4755 868.9817) 
(list 3200.4755 868.9919) 
(list 3200.4755 869.0022) 
(list 3200.4755 869.0125) 
(list 3200.4755 869.0228) 
(list 3200.4755 869.0331) 
(list 3200.4755 869.0433) 
(list 3200.4755 869.0536) 
(list 3200.4755 869.0639) 
(list 3200.4755 869.0742) 
(list 3200.4755 869.0844) 
(list 3200.4755 869.0947) 
(list 3200.4755 869.105) 
(list 3200.4755 869.1153) 
(list 3200.4755 869.1256) 
(list 3200.4755 869.1358) 
(list 3200.4755 869.1461) 
(list 3200.4755 869.1564) 
(list 3200.4755 869.1667) 
(list 3200.4755 869.1769) 
(list 3200.4755 869.1872) 
(list 3200.4755 869.1975) 
(list 3200.4755 869.2078) 
(list 3200.4755 869.2181) 
(list 3200.4755 869.2283) 
(list 3200.4755 869.2386) 
(list 3200.4755 869.2489) 
(list 3200.4755 869.2592) 
(list 3200.4755 869.2694) 
(list 3200.4755 869.2797) 
(list 3200.4755 869.29) 
(list 3201.112 869.29)))
(apply 'command (append '("pline") coords '("c")))
(setq tap10 (ssadd (entlast) tap10))
(command "_mirror" (entlast) "" "3200,900" "3200,901" "No")
(setq tap10 (ssadd (entlast) tap10))
(setq coords (list 
(list 3200 869.29) 
(list 3200.125 869.29) 
(list 3200.125 869.3003) 
(list 3200.125 869.3106) 
(list 3200.125 869.3208) 
(list 3200.125 869.3311) 
(list 3200.125 869.3414) 
(list 3200.125 869.3517) 
(list 3200.125 869.3619) 
(list 3200.125 869.3722) 
(list 3200.125 869.3825) 
(list 3200.125 869.3928) 
(list 3200.125 869.4031) 
(list 3200.125 869.4133) 
(list 3200.125 869.4236) 
(list 3200.125 869.4339) 
(list 3200.125 869.4442) 
(list 3200.125 869.4544) 
(list 3200.125 869.4647) 
(list 3200.125 869.475) 
(list 3200.125 869.4853) 
(list 3200.125 869.4956) 
(list 3200.125 869.5058) 
(list 3200.125 869.5161) 
(list 3200.125 869.5264) 
(list 3200.125 869.5367) 
(list 3200.125 869.5469) 
(list 3200.125 869.5572) 
(list 3200.125 869.5675) 
(list 3200.125 869.5778) 
(list 3200.125 869.5881) 
(list 3200.125 869.5983) 
(list 3200.125 869.6086) 
(list 3200.125 869.6189) 
(list 3200.125 869.6292) 
(list 3200.125 869.6394) 
(list 3200.125 869.6497) 
(list 3200.125 869.66) 
(list 3200 869.66)))
(apply 'command (append '("pline") coords '("c")))
(setq tap10 (ssadd (entlast) tap10))
(command "_mirror" (entlast) "" "3200,900" "3200,901" "No")
(setq tap10 (ssadd (entlast) tap10))
(setq coords (list 
(list 3200.4855 869.29) 
(list 3200.4755 869.29) 
(list 3200.4748 869.3003) 
(list 3200.4723 869.3106) 
(list 3200.468 869.3208) 
(list 3200.4619 869.3311) 
(list 3200.4544 869.3414) 
(list 3200.4456 869.3517) 
(list 3200.4358 869.3619) 
(list 3200.4252 869.3722) 
(list 3200.4142 869.3825) 
(list 3200.4031 869.3928) 
(list 3200.3923 869.4031) 
(list 3200.382 869.4133) 
(list 3200.3727 869.4236) 
(list 3200.3645 869.4339) 
(list 3200.3579 869.4442) 
(list 3200.3529 869.4544) 
(list 3200.3497 869.4647) 
(list 3200.3485 869.475) 
(list 3200.3493 869.4853) 
(list 3200.3521 869.4956) 
(list 3200.3568 869.5058) 
(list 3200.3633 869.5161) 
(list 3200.3715 869.5264) 
(list 3200.381 869.5367) 
(list 3200.3916 869.5469) 
(list 3200.403 869.5572) 
(list 3200.4148 869.5675) 
(list 3200.4267 869.5778) 
(list 3200.4384 869.5881) 
(list 3200.4494 869.5983) 
(list 3200.4594 869.6086) 
(list 3200.4682 869.6189) 
(list 3200.4754 869.6292) 
(list 3200.4808 869.6394) 
(list 3200.4842 869.6497) 
(list 3200.4855 869.66) 
(list 3200.4855 869.66)))
(apply 'command (append '("pline") coords '("c")))
(setq tap10 (ssadd (entlast) tap10))
(command "_mirror" (entlast) "" "3200,900" "3200,901" "No")
(setq tap10 (ssadd (entlast) tap10))
(setq coords (list 
(list 3201.112 869.29) 
(list 3200.4855 869.29) 
(list 3200.4855 869.3003) 
(list 3200.4855 869.3106) 
(list 3200.4855 869.3208) 
(list 3200.4855 869.3311) 
(list 3200.4855 869.3414) 
(list 3200.4855 869.3517) 
(list 3200.4855 869.3619) 
(list 3200.4855 869.3722) 
(list 3200.4855 869.3825) 
(list 3200.4855 869.3928) 
(list 3200.4855 869.4031) 
(list 3200.4855 869.4133) 
(list 3200.4855 869.4236) 
(list 3200.4855 869.4339) 
(list 3200.4855 869.4442) 
(list 3200.4855 869.4544) 
(list 3200.4855 869.4647) 
(list 3200.4855 869.475) 
(list 3200.4855 869.4853) 
(list 3200.4855 869.4956) 
(list 3200.4855 869.5058) 
(list 3200.4855 869.5161) 
(list 3200.4855 869.5264) 
(list 3200.4855 869.5367) 
(list 3200.4855 869.5469) 
(list 3200.4855 869.5572) 
(list 3200.4855 869.5675) 
(list 3200.4855 869.5778) 
(list 3200.4855 869.5881) 
(list 3200.4855 869.5983) 
(list 3200.4855 869.6086) 
(list 3200.4855 869.6189) 
(list 3200.4855 869.6292) 
(list 3200.4855 869.6394) 
(list 3200.4855 869.6497) 
(list 3200.4855 869.66) 
(list 3201.112 869.66)))
(apply 'command (append '("pline") coords '("c")))
(setq tap10 (ssadd (entlast) tap10))
(command "_mirror" (entlast) "" "3200,900" "3200,901" "No")
(setq tap10 (ssadd (entlast) tap10))
(setq coords (list 
(list 3200 869.66) 
(list 3200.125 869.66) 
(list 3200.125 869.6703) 
(list 3200.125 869.6806) 
(list 3200.125 869.6908) 
(list 3200.125 869.7011) 
(list 3200.125 869.7114) 
(list 3200.125 869.7217) 
(list 3200.125 869.7319) 
(list 3200.125 869.7422) 
(list 3200.125 869.7525) 
(list 3200.125 869.7628) 
(list 3200.125 869.7731) 
(list 3200.125 869.7833) 
(list 3200.125 869.7936) 
(list 3200.125 869.8039) 
(list 3200.125 869.8142) 
(list 3200.125 869.8244) 
(list 3200.125 869.8347) 
(list 3200.125 869.845) 
(list 3200.125 869.8553) 
(list 3200.125 869.8656) 
(list 3200.125 869.8758) 
(list 3200.125 869.8861) 
(list 3200.125 869.8964) 
(list 3200.125 869.9067) 
(list 3200.125 869.9169) 
(list 3200.125 869.9272) 
(list 3200.125 869.9375) 
(list 3200.125 869.9478) 
(list 3200.125 869.9581) 
(list 3200.125 869.9683) 
(list 3200.125 869.9786) 
(list 3200.125 869.9889) 
(list 3200.125 869.9992) 
(list 3200.125 870.0094) 
(list 3200.125 870.0197) 
(list 3200.125 870.03) 
(list 3200 870.03)))
(apply 'command (append '("pline") coords '("c")))
(setq tap10 (ssadd (entlast) tap10))
(command "_mirror" (entlast) "" "3200,900" "3200,901" "No")
(setq tap10 (ssadd (entlast) tap10))
(setq coords (list 
(list 3200.4956 869.66) 
(list 3200.4855 869.66) 
(list 3200.4847 869.6703) 
(list 3200.4818 869.6806) 
(list 3200.4768 869.6908) 
(list 3200.47 869.7011) 
(list 3200.4613 869.7114) 
(list 3200.4513 869.7217) 
(list 3200.44 869.7319) 
(list 3200.428 869.7422) 
(list 3200.4154 869.7525) 
(list 3200.4028 869.7628) 
(list 3200.3905 869.7731) 
(list 3200.3789 869.7833) 
(list 3200.3683 869.7936) 
(list 3200.3591 869.8039) 
(list 3200.3515 869.8142) 
(list 3200.3459 869.8244) 
(list 3200.3423 869.8347) 
(list 3200.341 869.845) 
(list 3200.3419 869.8553) 
(list 3200.3451 869.8656) 
(list 3200.3505 869.8758) 
(list 3200.3579 869.8861) 
(list 3200.3671 869.8964) 
(list 3200.3778 869.9067) 
(list 3200.3898 869.9169) 
(list 3200.4027 869.9272) 
(list 3200.4161 869.9375) 
(list 3200.4295 869.9478) 
(list 3200.4427 869.9581) 
(list 3200.4551 869.9683) 
(list 3200.4663 869.9786) 
(list 3200.4762 869.9889) 
(list 3200.4842 869.9992) 
(list 3200.4903 870.0094) 
(list 3200.4941 870.0197) 
(list 3200.4956 870.03) 
(list 3200.4956 870.03)))
(apply 'command (append '("pline") coords '("c")))
(setq tap10 (ssadd (entlast) tap10))
(command "_mirror" (entlast) "" "3200,900" "3200,901" "No")
(setq tap10 (ssadd (entlast) tap10))
(setq coords (list 
(list 3201.112 869.66) 
(list 3200.4956 869.66) 
(list 3200.4956 869.6703) 
(list 3200.4956 869.6806) 
(list 3200.4956 869.6908) 
(list 3200.4956 869.7011) 
(list 3200.4956 869.7114) 
(list 3200.4956 869.7217) 
(list 3200.4956 869.7319) 
(list 3200.4956 869.7422) 
(list 3200.4956 869.7525) 
(list 3200.4956 869.7628) 
(list 3200.4956 869.7731) 
(list 3200.4956 869.7833) 
(list 3200.4956 869.7936) 
(list 3200.4956 869.8039) 
(list 3200.4956 869.8142) 
(list 3200.4956 869.8244) 
(list 3200.4956 869.8347) 
(list 3200.4956 869.845) 
(list 3200.4956 869.8553) 
(list 3200.4956 869.8656) 
(list 3200.4956 869.8758) 
(list 3200.4956 869.8861) 
(list 3200.4956 869.8964) 
(list 3200.4956 869.9067) 
(list 3200.4956 869.9169) 
(list 3200.4956 869.9272) 
(list 3200.4956 869.9375) 
(list 3200.4956 869.9478) 
(list 3200.4956 869.9581) 
(list 3200.4956 869.9683) 
(list 3200.4956 869.9786) 
(list 3200.4956 869.9889) 
(list 3200.4956 869.9992) 
(list 3200.4956 870.0094) 
(list 3200.4956 870.0197) 
(list 3200.4956 870.03) 
(list 3201.112 870.03)))
(apply 'command (append '("pline") coords '("c")))
(setq tap10 (ssadd (entlast) tap10))
(command "_mirror" (entlast) "" "3200,900" "3200,901" "No")
(setq tap10 (ssadd (entlast) tap10))
(setq coords (list 
(list 3200 870.03) 
(list 3200.125 870.03) 
(list 3200.125 870.0403) 
(list 3200.125 870.0506) 
(list 3200.125 870.0608) 
(list 3200.125 870.0711) 
(list 3200.125 870.0814) 
(list 3200.125 870.0917) 
(list 3200.125 870.1019) 
(list 3200.125 870.1122) 
(list 3200.125 870.1225) 
(list 3200.125 870.1328) 
(list 3200.125 870.1431) 
(list 3200.125 870.1533) 
(list 3200.125 870.1636) 
(list 3200.125 870.1739) 
(list 3200.125 870.1842) 
(list 3200.125 870.1944) 
(list 3200.125 870.2047) 
(list 3200.125 870.215) 
(list 3200.125 870.2253) 
(list 3200.125 870.2356) 
(list 3200.125 870.2458) 
(list 3200.125 870.2561) 
(list 3200.125 870.2664) 
(list 3200.125 870.2767) 
(list 3200.125 870.2869) 
(list 3200.125 870.2972) 
(list 3200.125 870.3075) 
(list 3200.125 870.3178) 
(list 3200.125 870.3281) 
(list 3200.125 870.3383) 
(list 3200.125 870.3486) 
(list 3200.125 870.3589) 
(list 3200.125 870.3692) 
(list 3200.125 870.3794) 
(list 3200.125 870.3897) 
(list 3200.125 870.4) 
(list 3200 870.4)))
(apply 'command (append '("pline") coords '("c")))
(setq tap10 (ssadd (entlast) tap10))
(command "_mirror" (entlast) "" "3200,900" "3200,901" "No")
(setq tap10 (ssadd (entlast) tap10))
(setq coords (list 
(list 3200.5057 870.03) 
(list 3200.4956 870.03) 
(list 3200.4947 870.0403) 
(list 3200.4914 870.0506) 
(list 3200.4857 870.0608) 
(list 3200.478 870.0711) 
(list 3200.4683 870.0814) 
(list 3200.4569 870.0917) 
(list 3200.4443 870.1019) 
(list 3200.4308 870.1122) 
(list 3200.4167 870.1225) 
(list 3200.4026 870.1328) 
(list 3200.3888 870.1431) 
(list 3200.3758 870.1533) 
(list 3200.3639 870.1636) 
(list 3200.3536 870.1739) 
(list 3200.3452 870.1842) 
(list 3200.3389 870.1944) 
(list 3200.3349 870.2047) 
(list 3200.3334 870.215) 
(list 3200.3345 870.2253) 
(list 3200.3381 870.2356) 
(list 3200.3441 870.2458) 
(list 3200.3524 870.2561) 
(list 3200.3627 870.2664) 
(list 3200.3747 870.2767) 
(list 3200.3881 870.2869) 
(list 3200.4025 870.2972) 
(list 3200.4174 870.3075) 
(list 3200.4323 870.3178) 
(list 3200.4469 870.3281) 
(list 3200.4607 870.3383) 
(list 3200.4733 870.3486) 
(list 3200.4842 870.3589) 
(list 3200.4931 870.3692) 
(list 3200.4998 870.3794) 
(list 3200.5041 870.3897) 
(list 3200.5057 870.4) 
(list 3200.5057 870.4)))
(apply 'command (append '("pline") coords '("c")))
(setq tap10 (ssadd (entlast) tap10))
(command "_mirror" (entlast) "" "3200,900" "3200,901" "No")
(setq tap10 (ssadd (entlast) tap10))
(setq coords (list 
(list 3201.112 870.03) 
(list 3200.5057 870.03) 
(list 3200.5057 870.0403) 
(list 3200.5057 870.0506) 
(list 3200.5057 870.0608) 
(list 3200.5057 870.0711) 
(list 3200.5057 870.0814) 
(list 3200.5057 870.0917) 
(list 3200.5057 870.1019) 
(list 3200.5057 870.1122) 
(list 3200.5057 870.1225) 
(list 3200.5057 870.1328) 
(list 3200.5057 870.1431) 
(list 3200.5057 870.1533) 
(list 3200.5057 870.1636) 
(list 3200.5057 870.1739) 
(list 3200.5057 870.1842) 
(list 3200.5057 870.1944) 
(list 3200.5057 870.2047) 
(list 3200.5057 870.215) 
(list 3200.5057 870.2253) 
(list 3200.5057 870.2356) 
(list 3200.5057 870.2458) 
(list 3200.5057 870.2561) 
(list 3200.5057 870.2664) 
(list 3200.5057 870.2767) 
(list 3200.5057 870.2869) 
(list 3200.5057 870.2972) 
(list 3200.5057 870.3075) 
(list 3200.5057 870.3178) 
(list 3200.5057 870.3281) 
(list 3200.5057 870.3383) 
(list 3200.5057 870.3486) 
(list 3200.5057 870.3589) 
(list 3200.5057 870.3692) 
(list 3200.5057 870.3794) 
(list 3200.5057 870.3897) 
(list 3200.5057 870.4) 
(list 3201.112 870.4)))
(apply 'command (append '("pline") coords '("c")))
(setq tap10 (ssadd (entlast) tap10))
(command "_mirror" (entlast) "" "3200,900" "3200,901" "No")
(setq tap10 (ssadd (entlast) tap10))
(setq coords (list 
(list 3200 870.4) 
(list 3200.125 870.4) 
(list 3200.125 870.4103) 
(list 3200.125 870.4206) 
(list 3200.125 870.4308) 
(list 3200.125 870.4411) 
(list 3200.125 870.4514) 
(list 3200.125 870.4617) 
(list 3200.125 870.4719) 
(list 3200.125 870.4822) 
(list 3200.125 870.4925) 
(list 3200.125 870.5028) 
(list 3200.125 870.5131) 
(list 3200.125 870.5233) 
(list 3200.125 870.5336) 
(list 3200.125 870.5439) 
(list 3200.125 870.5542) 
(list 3200.125 870.5644) 
(list 3200.125 870.5747) 
(list 3200.125 870.585) 
(list 3200.125 870.5953) 
(list 3200.125 870.6056) 
(list 3200.125 870.6158) 
(list 3200.125 870.6261) 
(list 3200.125 870.6364) 
(list 3200.125 870.6467) 
(list 3200.125 870.6569) 
(list 3200.125 870.6672) 
(list 3200.125 870.6775) 
(list 3200.125 870.6878) 
(list 3200.125 870.6981) 
(list 3200.125 870.7083) 
(list 3200.125 870.7186) 
(list 3200.125 870.7289) 
(list 3200.125 870.7392) 
(list 3200.125 870.7494) 
(list 3200.125 870.7597) 
(list 3200.125 870.77) 
(list 3200 870.77)))
(apply 'command (append '("pline") coords '("c")))
(setq tap10 (ssadd (entlast) tap10))
(command "_mirror" (entlast) "" "3200,900" "3200,901" "No")
(setq tap10 (ssadd (entlast) tap10))
(setq coords (list 
(list 3200.5157 870.4) 
(list 3200.5057 870.4) 
(list 3200.5046 870.4103) 
(list 3200.5009 870.4206) 
(list 3200.4946 870.4308) 
(list 3200.486 870.4411) 
(list 3200.4752 870.4514) 
(list 3200.4626 870.4617) 
(list 3200.4486 870.4719) 
(list 3200.4336 870.4822) 
(list 3200.418 870.4925) 
(list 3200.4023 870.5028) 
(list 3200.387 870.5131) 
(list 3200.3726 870.5233) 
(list 3200.3595 870.5336) 
(list 3200.3481 870.5439) 
(list 3200.3388 870.5542) 
(list 3200.3319 870.5644) 
(list 3200.3275 870.5747) 
(list 3200.3259 870.585) 
(list 3200.3271 870.5953) 
(list 3200.3311 870.6056) 
(list 3200.3378 870.6158) 
(list 3200.3469 870.6261) 
(list 3200.3583 870.6364) 
(list 3200.3716 870.6467) 
(list 3200.3864 870.6569) 
(list 3200.4022 870.6672) 
(list 3200.4186 870.6775) 
(list 3200.4351 870.6878) 
(list 3200.4512 870.6981) 
(list 3200.4664 870.7083) 
(list 3200.4802 870.7186) 
(list 3200.4922 870.7289) 
(list 3200.502 870.7392) 
(list 3200.5094 870.7494) 
(list 3200.514 870.7597) 
(list 3200.5157 870.77) 
(list 3200.5157 870.77)))
(apply 'command (append '("pline") coords '("c")))
(setq tap10 (ssadd (entlast) tap10))
(command "_mirror" (entlast) "" "3200,900" "3200,901" "No")
(setq tap10 (ssadd (entlast) tap10))
(setq coords (list 
(list 3201.112 870.4) 
(list 3200.5157 870.4) 
(list 3200.5157 870.4103) 
(list 3200.5157 870.4206) 
(list 3200.5157 870.4308) 
(list 3200.5157 870.4411) 
(list 3200.5157 870.4514) 
(list 3200.5157 870.4617) 
(list 3200.5157 870.4719) 
(list 3200.5157 870.4822) 
(list 3200.5157 870.4925) 
(list 3200.5157 870.5028) 
(list 3200.5157 870.5131) 
(list 3200.5157 870.5233) 
(list 3200.5157 870.5336) 
(list 3200.5157 870.5439) 
(list 3200.5157 870.5542) 
(list 3200.5157 870.5644) 
(list 3200.5157 870.5747) 
(list 3200.5157 870.585) 
(list 3200.5157 870.5953) 
(list 3200.5157 870.6056) 
(list 3200.5157 870.6158) 
(list 3200.5157 870.6261) 
(list 3200.5157 870.6364) 
(list 3200.5157 870.6467) 
(list 3200.5157 870.6569) 
(list 3200.5157 870.6672) 
(list 3200.5157 870.6775) 
(list 3200.5157 870.6878) 
(list 3200.5157 870.6981) 
(list 3200.5157 870.7083) 
(list 3200.5157 870.7186) 
(list 3200.5157 870.7289) 
(list 3200.5157 870.7392) 
(list 3200.5157 870.7494) 
(list 3200.5157 870.7597) 
(list 3200.5157 870.77) 
(list 3201.112 870.77)))
(apply 'command (append '("pline") coords '("c")))
(setq tap10 (ssadd (entlast) tap10))
(command "_mirror" (entlast) "" "3200,900" "3200,901" "No")
(setq tap10 (ssadd (entlast) tap10))
(setq coords (list 
(list 3200 870.77) 
(list 3200.125 870.77) 
(list 3200.125 870.7803) 
(list 3200.125 870.7906) 
(list 3200.125 870.8008) 
(list 3200.125 870.8111) 
(list 3200.125 870.8214) 
(list 3200.125 870.8317) 
(list 3200.125 870.8419) 
(list 3200.125 870.8522) 
(list 3200.125 870.8625) 
(list 3200.125 870.8728) 
(list 3200.125 870.8831) 
(list 3200.125 870.8933) 
(list 3200.125 870.9036) 
(list 3200.125 870.9139) 
(list 3200.125 870.9242) 
(list 3200.125 870.9344) 
(list 3200.125 870.9447) 
(list 3200.125 870.955) 
(list 3200.125 870.9653) 
(list 3200.125 870.9756) 
(list 3200.125 870.9858) 
(list 3200.125 870.9961) 
(list 3200.125 871.0064) 
(list 3200.125 871.0167) 
(list 3200.125 871.0269) 
(list 3200.125 871.0372) 
(list 3200.125 871.0475) 
(list 3200.125 871.0578) 
(list 3200.125 871.0681) 
(list 3200.125 871.0783) 
(list 3200.125 871.0886) 
(list 3200.125 871.0989) 
(list 3200.125 871.1092) 
(list 3200.125 871.1194) 
(list 3200.125 871.1297) 
(list 3200.125 871.14) 
(list 3200 871.14)))
(apply 'command (append '("pline") coords '("c")))
(setq tap10 (ssadd (entlast) tap10))
(command "_mirror" (entlast) "" "3200,900" "3200,901" "No")
(setq tap10 (ssadd (entlast) tap10))
(setq coords (list 
(list 3200.5258 870.77) 
(list 3200.5157 870.77) 
(list 3200.5145 870.7803) 
(list 3200.5104 870.7906) 
(list 3200.5035 870.8008) 
(list 3200.494 870.8111) 
(list 3200.4821 870.8214) 
(list 3200.4683 870.8317) 
(list 3200.4529 870.8419) 
(list 3200.4364 870.8522) 
(list 3200.4192 870.8625) 
(list 3200.4021 870.8728) 
(list 3200.3853 870.8831) 
(list 3200.3695 870.8933) 
(list 3200.3551 870.9036) 
(list 3200.3427 870.9139) 
(list 3200.3325 870.9242) 
(list 3200.3249 870.9344) 
(list 3200.3201 870.9447) 
(list 3200.3184 870.955) 
(list 3200.3197 870.9653) 
(list 3200.3241 870.9756) 
(list 3200.3314 870.9858) 
(list 3200.3414 870.9961) 
(list 3200.3539 871.0064) 
(list 3200.3684 871.0167) 
(list 3200.3846 871.0269) 
(list 3200.4019 871.0372) 
(list 3200.4199 871.0475) 
(list 3200.4379 871.0578) 
(list 3200.4555 871.0681) 
(list 3200.4721 871.0783) 
(list 3200.4871 871.0886) 
(list 3200.5002 871.0989) 
(list 3200.5109 871.1092) 
(list 3200.5189 871.1194) 
(list 3200.5239 871.1297) 
(list 3200.5258 871.14) 
(list 3200.5258 871.14)))
(apply 'command (append '("pline") coords '("c")))
(setq tap10 (ssadd (entlast) tap10))
(command "_mirror" (entlast) "" "3200,900" "3200,901" "No")
(setq tap10 (ssadd (entlast) tap10))
(setq coords (list 
(list 3201.112 870.77) 
(list 3200.5258 870.77) 
(list 3200.5258 870.7803) 
(list 3200.5258 870.7906) 
(list 3200.5258 870.8008) 
(list 3200.5258 870.8111) 
(list 3200.5258 870.8214) 
(list 3200.5258 870.8317) 
(list 3200.5258 870.8419) 
(list 3200.5258 870.8522) 
(list 3200.5258 870.8625) 
(list 3200.5258 870.8728) 
(list 3200.5258 870.8831) 
(list 3200.5258 870.8933) 
(list 3200.5258 870.9036) 
(list 3200.5258 870.9139) 
(list 3200.5258 870.9242) 
(list 3200.5258 870.9344) 
(list 3200.5258 870.9447) 
(list 3200.5258 870.955) 
(list 3200.5258 870.9653) 
(list 3200.5258 870.9756) 
(list 3200.5258 870.9858) 
(list 3200.5258 870.9961) 
(list 3200.5258 871.0064) 
(list 3200.5258 871.0167) 
(list 3200.5258 871.0269) 
(list 3200.5258 871.0372) 
(list 3200.5258 871.0475) 
(list 3200.5258 871.0578) 
(list 3200.5258 871.0681) 
(list 3200.5258 871.0783) 
(list 3200.5258 871.0886) 
(list 3200.5258 871.0989) 
(list 3200.5258 871.1092) 
(list 3200.5258 871.1194) 
(list 3200.5258 871.1297) 
(list 3200.5258 871.14) 
(list 3201.112 871.14)))
(apply 'command (append '("pline") coords '("c")))
(setq tap10 (ssadd (entlast) tap10))
(command "_mirror" (entlast) "" "3200,900" "3200,901" "No")
(setq tap10 (ssadd (entlast) tap10))
(setq coords (list 
(list 3200 871.14) 
(list 3200.125 871.14) 
(list 3200.125 871.1503) 
(list 3200.125 871.1606) 
(list 3200.125 871.1708) 
(list 3200.125 871.1811) 
(list 3200.125 871.1914) 
(list 3200.125 871.2017) 
(list 3200.125 871.2119) 
(list 3200.125 871.2222) 
(list 3200.125 871.2325) 
(list 3200.125 871.2428) 
(list 3200.125 871.2531) 
(list 3200.125 871.2633) 
(list 3200.125 871.2736) 
(list 3200.125 871.2839) 
(list 3200.125 871.2942) 
(list 3200.125 871.3044) 
(list 3200.125 871.3147) 
(list 3200.125 871.325) 
(list 3200.125 871.3353) 
(list 3200.125 871.3456) 
(list 3200.125 871.3558) 
(list 3200.125 871.3661) 
(list 3200.125 871.3764) 
(list 3200.125 871.3867) 
(list 3200.125 871.3969) 
(list 3200.125 871.4072) 
(list 3200.125 871.4175) 
(list 3200.125 871.4278) 
(list 3200.125 871.4381) 
(list 3200.125 871.4483) 
(list 3200.125 871.4586) 
(list 3200.125 871.4689) 
(list 3200.125 871.4792) 
(list 3200.125 871.4894) 
(list 3200.125 871.4997) 
(list 3200.125 871.51) 
(list 3200 871.51)))
(apply 'command (append '("pline") coords '("c")))
(setq tap10 (ssadd (entlast) tap10))
(command "_mirror" (entlast) "" "3200,900" "3200,901" "No")
(setq tap10 (ssadd (entlast) tap10))
(setq coords (list 
(list 3200.5359 871.14) 
(list 3200.5258 871.14) 
(list 3200.5245 871.1503) 
(list 3200.52 871.1606) 
(list 3200.5124 871.1708) 
(list 3200.502 871.1811) 
(list 3200.489 871.1914) 
(list 3200.4739 871.2017) 
(list 3200.4571 871.2119) 
(list 3200.4392 871.2222) 
(list 3200.4205 871.2325) 
(list 3200.4018 871.2428) 
(list 3200.3836 871.2531) 
(list 3200.3664 871.2633) 
(list 3200.3507 871.2736) 
(list 3200.3372 871.2839) 
(list 3200.3261 871.2942) 
(list 3200.3179 871.3044) 
(list 3200.3127 871.3147) 
(list 3200.3108 871.325) 
(list 3200.3123 871.3353) 
(list 3200.3171 871.3456) 
(list 3200.325 871.3558) 
(list 3200.336 871.3661) 
(list 3200.3495 871.3764) 
(list 3200.3653 871.3867) 
(list 3200.3829 871.3969) 
(list 3200.4017 871.4072) 
(list 3200.4212 871.4175) 
(list 3200.4407 871.4278) 
(list 3200.4598 871.4381) 
(list 3200.4777 871.4483) 
(list 3200.494 871.4586) 
(list 3200.5082 871.4689) 
(list 3200.5198 871.4792) 
(list 3200.5284 871.4894) 
(list 3200.5339 871.4997) 
(list 3200.5359 871.51) 
(list 3200.5359 871.51)))
(apply 'command (append '("pline") coords '("c")))
(setq tap10 (ssadd (entlast) tap10))
(command "_mirror" (entlast) "" "3200,900" "3200,901" "No")
(setq tap10 (ssadd (entlast) tap10))
(setq coords (list 
(list 3201.112 871.14) 
(list 3200.5359 871.14) 
(list 3200.5359 871.1503) 
(list 3200.5359 871.1606) 
(list 3200.5359 871.1708) 
(list 3200.5359 871.1811) 
(list 3200.5359 871.1914) 
(list 3200.5359 871.2017) 
(list 3200.5359 871.2119) 
(list 3200.5359 871.2222) 
(list 3200.5359 871.2325) 
(list 3200.5359 871.2428) 
(list 3200.5359 871.2531) 
(list 3200.5359 871.2633) 
(list 3200.5359 871.2736) 
(list 3200.5359 871.2839) 
(list 3200.5359 871.2942) 
(list 3200.5359 871.3044) 
(list 3200.5359 871.3147) 
(list 3200.5359 871.325) 
(list 3200.5359 871.3353) 
(list 3200.5359 871.3456) 
(list 3200.5359 871.3558) 
(list 3200.5359 871.3661) 
(list 3200.5359 871.3764) 
(list 3200.5359 871.3867) 
(list 3200.5359 871.3969) 
(list 3200.5359 871.4072) 
(list 3200.5359 871.4175) 
(list 3200.5359 871.4278) 
(list 3200.5359 871.4381) 
(list 3200.5359 871.4483) 
(list 3200.5359 871.4586) 
(list 3200.5359 871.4689) 
(list 3200.5359 871.4792) 
(list 3200.5359 871.4894) 
(list 3200.5359 871.4997) 
(list 3200.5359 871.51) 
(list 3201.112 871.51)))
(apply 'command (append '("pline") coords '("c")))
(setq tap10 (ssadd (entlast) tap10))
(command "_mirror" (entlast) "" "3200,900" "3200,901" "No")
(setq tap10 (ssadd (entlast) tap10))
(setq coords (list 
(list 3200 871.51) 
(list 3200.125 871.51) 
(list 3200.125 871.5203) 
(list 3200.125 871.5306) 
(list 3200.125 871.5408) 
(list 3200.125 871.5511) 
(list 3200.125 871.5614) 
(list 3200.125 871.5717) 
(list 3200.125 871.5819) 
(list 3200.125 871.5922) 
(list 3200.125 871.6025) 
(list 3200.125 871.6128) 
(list 3200.125 871.6231) 
(list 3200.125 871.6333) 
(list 3200.125 871.6436) 
(list 3200.125 871.6539) 
(list 3200.125 871.6642) 
(list 3200.125 871.6744) 
(list 3200.125 871.6847) 
(list 3200.125 871.695) 
(list 3200.125 871.7053) 
(list 3200.125 871.7156) 
(list 3200.125 871.7258) 
(list 3200.125 871.7361) 
(list 3200.125 871.7464) 
(list 3200.125 871.7567) 
(list 3200.125 871.7669) 
(list 3200.125 871.7772) 
(list 3200.125 871.7875) 
(list 3200.125 871.7978) 
(list 3200.125 871.8081) 
(list 3200.125 871.8183) 
(list 3200.125 871.8286) 
(list 3200.125 871.8389) 
(list 3200.125 871.8492) 
(list 3200.125 871.8594) 
(list 3200.125 871.8697) 
(list 3200.125 871.88) 
(list 3200 871.88)))
(apply 'command (append '("pline") coords '("c")))
(setq tap10 (ssadd (entlast) tap10))
(command "_mirror" (entlast) "" "3200,900" "3200,901" "No")
(setq tap10 (ssadd (entlast) tap10))
(setq coords (list 
(list 3200.5459 871.51) 
(list 3200.5359 871.51) 
(list 3200.5344 871.5203) 
(list 3200.5295 871.5306) 
(list 3200.5213 871.5408) 
(list 3200.51 871.5511) 
(list 3200.496 871.5614) 
(list 3200.4796 871.5717) 
(list 3200.4614 871.5819) 
(list 3200.442 871.5922) 
(list 3200.4218 871.6025) 
(list 3200.4015 871.6128) 
(list 3200.3818 871.6231) 
(list 3200.3632 871.6333) 
(list 3200.3463 871.6436) 
(list 3200.3317 871.6539) 
(list 3200.3197 871.6642) 
(list 3200.3109 871.6744) 
(list 3200.3053 871.6847) 
(list 3200.3033 871.695) 
(list 3200.3049 871.7053) 
(list 3200.3101 871.7156) 
(list 3200.3187 871.7258) 
(list 3200.3305 871.7361) 
(list 3200.3451 871.7464) 
(list 3200.3622 871.7567) 
(list 3200.3811 871.7669) 
(list 3200.4014 871.7772) 
(list 3200.4224 871.7875) 
(list 3200.4435 871.7978) 
(list 3200.464 871.8081) 
(list 3200.4834 871.8183) 
(list 3200.501 871.8286) 
(list 3200.5162 871.8389) 
(list 3200.5287 871.8492) 
(list 3200.538 871.8594) 
(list 3200.5438 871.8697) 
(list 3200.5459 871.88) 
(list 3200.5459 871.88)))
(apply 'command (append '("pline") coords '("c")))
(setq tap10 (ssadd (entlast) tap10))
(command "_mirror" (entlast) "" "3200,900" "3200,901" "No")
(setq tap10 (ssadd (entlast) tap10))
(setq coords (list 
(list 3201.112 871.51) 
(list 3200.5459 871.51) 
(list 3200.5459 871.5203) 
(list 3200.5459 871.5306) 
(list 3200.5459 871.5408) 
(list 3200.5459 871.5511) 
(list 3200.5459 871.5614) 
(list 3200.5459 871.5717) 
(list 3200.5459 871.5819) 
(list 3200.5459 871.5922) 
(list 3200.5459 871.6025) 
(list 3200.5459 871.6128) 
(list 3200.5459 871.6231) 
(list 3200.5459 871.6333) 
(list 3200.5459 871.6436) 
(list 3200.5459 871.6539) 
(list 3200.5459 871.6642) 
(list 3200.5459 871.6744) 
(list 3200.5459 871.6847) 
(list 3200.5459 871.695) 
(list 3200.5459 871.7053) 
(list 3200.5459 871.7156) 
(list 3200.5459 871.7258) 
(list 3200.5459 871.7361) 
(list 3200.5459 871.7464) 
(list 3200.5459 871.7567) 
(list 3200.5459 871.7669) 
(list 3200.5459 871.7772) 
(list 3200.5459 871.7875) 
(list 3200.5459 871.7978) 
(list 3200.5459 871.8081) 
(list 3200.5459 871.8183) 
(list 3200.5459 871.8286) 
(list 3200.5459 871.8389) 
(list 3200.5459 871.8492) 
(list 3200.5459 871.8594) 
(list 3200.5459 871.8697) 
(list 3200.5459 871.88) 
(list 3201.112 871.88)))
(apply 'command (append '("pline") coords '("c")))
(setq tap10 (ssadd (entlast) tap10))
(command "_mirror" (entlast) "" "3200,900" "3200,901" "No")
(setq tap10 (ssadd (entlast) tap10))
(setq coords (list 
(list 3200 871.88) 
(list 3200.125 871.88) 
(list 3200.125 871.8903) 
(list 3200.125 871.9006) 
(list 3200.125 871.9108) 
(list 3200.125 871.9211) 
(list 3200.125 871.9314) 
(list 3200.125 871.9417) 
(list 3200.125 871.9519) 
(list 3200.125 871.9622) 
(list 3200.125 871.9725) 
(list 3200.125 871.9828) 
(list 3200.125 871.9931) 
(list 3200.125 872.0033) 
(list 3200.125 872.0136) 
(list 3200.125 872.0239) 
(list 3200.125 872.0342) 
(list 3200.125 872.0444) 
(list 3200.125 872.0547) 
(list 3200.125 872.065) 
(list 3200.125 872.0753) 
(list 3200.125 872.0856) 
(list 3200.125 872.0958) 
(list 3200.125 872.1061) 
(list 3200.125 872.1164) 
(list 3200.125 872.1267) 
(list 3200.125 872.1369) 
(list 3200.125 872.1472) 
(list 3200.125 872.1575) 
(list 3200.125 872.1678) 
(list 3200.125 872.1781) 
(list 3200.125 872.1883) 
(list 3200.125 872.1986) 
(list 3200.125 872.2089) 
(list 3200.125 872.2192) 
(list 3200.125 872.2294) 
(list 3200.125 872.2397) 
(list 3200.125 872.25) 
(list 3200 872.25)))
(apply 'command (append '("pline") coords '("c")))
(setq tap10 (ssadd (entlast) tap10))
(command "_mirror" (entlast) "" "3200,900" "3200,901" "No")
(setq tap10 (ssadd (entlast) tap10))
(setq coords (list 
(list 3200.556 871.88) 
(list 3200.5459 871.88) 
(list 3200.5443 871.8903) 
(list 3200.539 871.9006) 
(list 3200.5302 871.9108) 
(list 3200.518 871.9211) 
(list 3200.5029 871.9314) 
(list 3200.4853 871.9417) 
(list 3200.4657 871.9519) 
(list 3200.4447 871.9622) 
(list 3200.423 871.9725) 
(list 3200.4013 871.9828) 
(list 3200.3801 871.9931) 
(list 3200.3601 872.0033) 
(list 3200.342 872.0136) 
(list 3200.3262 872.0239) 
(list 3200.3134 872.0342) 
(list 3200.3039 872.0444) 
(list 3200.2979 872.0547) 
(list 3200.2958 872.065) 
(list 3200.2975 872.0753) 
(list 3200.3031 872.0856) 
(list 3200.3123 872.0958) 
(list 3200.325 872.1061) 
(list 3200.3407 872.1164) 
(list 3200.359 872.1267) 
(list 3200.3794 872.1369) 
(list 3200.4012 872.1472) 
(list 3200.4237 872.1575) 
(list 3200.4463 872.1678) 
(list 3200.4683 872.1781) 
(list 3200.4891 872.1883) 
(list 3200.5079 872.1986) 
(list 3200.5242 872.2089) 
(list 3200.5376 872.2192) 
(list 3200.5475 872.2294) 
(list 3200.5537 872.2397) 
(list 3200.556 872.25) 
(list 3200.556 872.25)))
(apply 'command (append '("pline") coords '("c")))
(setq tap10 (ssadd (entlast) tap10))
(command "_mirror" (entlast) "" "3200,900" "3200,901" "No")
(setq tap10 (ssadd (entlast) tap10))
(setq coords (list 
(list 3201.112 871.88) 
(list 3200.556 871.88) 
(list 3200.556 871.8903) 
(list 3200.556 871.9006) 
(list 3200.556 871.9108) 
(list 3200.556 871.9211) 
(list 3200.556 871.9314) 
(list 3200.556 871.9417) 
(list 3200.556 871.9519) 
(list 3200.556 871.9622) 
(list 3200.556 871.9725) 
(list 3200.556 871.9828) 
(list 3200.556 871.9931) 
(list 3200.556 872.0033) 
(list 3200.556 872.0136) 
(list 3200.556 872.0239) 
(list 3200.556 872.0342) 
(list 3200.556 872.0444) 
(list 3200.556 872.0547) 
(list 3200.556 872.065) 
(list 3200.556 872.0753) 
(list 3200.556 872.0856) 
(list 3200.556 872.0958) 
(list 3200.556 872.1061) 
(list 3200.556 872.1164) 
(list 3200.556 872.1267) 
(list 3200.556 872.1369) 
(list 3200.556 872.1472) 
(list 3200.556 872.1575) 
(list 3200.556 872.1678) 
(list 3200.556 872.1781) 
(list 3200.556 872.1883) 
(list 3200.556 872.1986) 
(list 3200.556 872.2089) 
(list 3200.556 872.2192) 
(list 3200.556 872.2294) 
(list 3200.556 872.2397) 
(list 3200.556 872.25) 
(list 3201.112 872.25)))
(apply 'command (append '("pline") coords '("c")))
(setq tap10 (ssadd (entlast) tap10))
(command "_mirror" (entlast) "" "3200,900" "3200,901" "No")
(setq tap10 (ssadd (entlast) tap10))
(command "_block" "blktap10" "3200,900" tap10 "")
(command "_insert" "blktap10" "3200,900" "1" "1" "0")
(command "_insert" "blktap10" "3200,900" "1" "1" "180")
(setq uc10 nil)
(setq uc10 (ssadd))
(setq coords (list 
(list 0 -0.185) 
(list 0.125 -0.185) 
(list 0.125 -0.17472) 
(list 0.125 -0.16444) 
(list 0.125 -0.15417) 
(list 0.125 -0.14389) 
(list 0.125 -0.13361) 
(list 0.125 -0.12333) 
(list 0.125 -0.11306) 
(list 0.125 -0.10278) 
(list 0.125 -0.0925) 
(list 0.125 -0.082222) 
(list 0.125 -0.071944) 
(list 0.125 -0.061667) 
(list 0.125 -0.051389) 
(list 0.125 -0.041111) 
(list 0.125 -0.030833) 
(list 0.125 -0.020556) 
(list 0.125 -0.010278) 
(list 0.125 0) 
(list 0.125 0.010278) 
(list 0.125 0.020556) 
(list 0.125 0.030833) 
(list 0.125 0.041111) 
(list 0.125 0.051389) 
(list 0.125 0.061667) 
(list 0.125 0.071944) 
(list 0.125 0.082222) 
(list 0.125 0.0925) 
(list 0.125 0.10278) 
(list 0.125 0.11306) 
(list 0.125 0.12333) 
(list 0.125 0.13361) 
(list 0.125 0.14389) 
(list 0.125 0.15417) 
(list 0.125 0.16444) 
(list 0.125 0.17472) 
(list 0.125 0.185) 
(list 0 0.185)))
(apply 'command (append '("pline") coords '("c")))
(setq uc10 (ssadd (entlast) uc10))
(setq coords (list 
(list 1.112 -0.185) 
(list 0.556 -0.185) 
(list 0.554 -0.17472) 
(list 0.54804 -0.16444) 
(list 0.53831 -0.15417) 
(list 0.52512 -0.14389) 
(list 0.50885 -0.13361) 
(list 0.49 -0.12333) 
(list 0.46915 -0.11306) 
(list 0.44692 -0.10278) 
(list 0.424 -0.0925) 
(list 0.40108 -0.082222) 
(list 0.37885 -0.071944) 
(list 0.358 -0.061667) 
(list 0.33915 -0.051389) 
(list 0.32288 -0.041111) 
(list 0.30968 -0.030833) 
(list 0.29996 -0.020556) 
(list 0.29401 -0.010278) 
(list 0.292 0) 
(list 0.29401 0.010278) 
(list 0.29996 0.020556) 
(list 0.30968 0.030833) 
(list 0.32288 0.041111) 
(list 0.33915 0.051389) 
(list 0.358 0.061667) 
(list 0.37885 0.071944) 
(list 0.40108 0.082222) 
(list 0.424 0.0925) 
(list 0.44692 0.10278) 
(list 0.46915 0.11306) 
(list 0.49 0.12333) 
(list 0.50885 0.13361) 
(list 0.52512 0.14389) 
(list 0.53831 0.15417) 
(list 0.54804 0.16444) 
(list 0.554 0.17472) 
(list 0.556 0.185) 
(list 1.112 0.185)))
(apply 'command (append '("pline") coords '("c")))
(setq uc10 (ssadd (entlast) uc10))
(command "_block" "blkuc10" "0,0.185" uc10 "")
(command "_insert" "blkuc10" "3200,872.62" "1" "1" "0")
(command "_insert" "blkuc10" "3200,872.25" "1" "1" "180")
(command "_insert" "blkuc10" "3200,872.99" "1" "1" "0")
(command "_insert" "blkuc10" "3200,872.62" "1" "1" "180")
(command "_insert" "blkuc10" "3200,873.36" "1" "1" "0")
(command "_insert" "blkuc10" "3200,872.99" "1" "1" "180")
(command "_insert" "blkuc10" "3200,873.73" "1" "1" "0")
(command "_insert" "blkuc10" "3200,873.36" "1" "1" "180")
(command "_insert" "blkuc10" "3200,874.1" "1" "1" "0")
(command "_insert" "blkuc10" "3200,873.73" "1" "1" "180")
(command "_insert" "blkuc10" "3200,874.47" "1" "1" "0")
(command "_insert" "blkuc10" "3200,874.1" "1" "1" "180")
(command "_insert" "blkuc10" "3200,874.84" "1" "1" "0")
(command "_insert" "blkuc10" "3200,874.47" "1" "1" "180")
(command "_insert" "blkuc10" "3200,875.21" "1" "1" "0")
(command "_insert" "blkuc10" "3200,874.84" "1" "1" "180")
(command "_insert" "blkuc10" "3200,875.58" "1" "1" "0")
(command "_insert" "blkuc10" "3200,875.21" "1" "1" "180")
(command "_insert" "blkuc10" "3200,875.95" "1" "1" "0")
(command "_insert" "blkuc10" "3200,875.58" "1" "1" "180")
(command "_insert" "blkuc10" "3200,876.32" "1" "1" "0")
(command "_insert" "blkuc10" "3200,875.95" "1" "1" "180")
(command "_insert" "blkuc10" "3200,876.69" "1" "1" "0")
(command "_insert" "blkuc10" "3200,876.32" "1" "1" "180")
(command "_insert" "blkuc10" "3200,877.06" "1" "1" "0")
(command "_insert" "blkuc10" "3200,876.69" "1" "1" "180")
(command "_insert" "blkuc10" "3200,877.43" "1" "1" "0")
(command "_insert" "blkuc10" "3200,877.06" "1" "1" "180")
(command "_insert" "blkuc10" "3200,877.8" "1" "1" "0")
(command "_insert" "blkuc10" "3200,877.43" "1" "1" "180")
(command "_insert" "blkuc10" "3200,878.17" "1" "1" "0")
(command "_insert" "blkuc10" "3200,877.8" "1" "1" "180")
(command "_insert" "blkuc10" "3200,878.54" "1" "1" "0")
(command "_insert" "blkuc10" "3200,878.17" "1" "1" "180")
(command "_insert" "blkuc10" "3200,878.91" "1" "1" "0")
(command "_insert" "blkuc10" "3200,878.54" "1" "1" "180")
(command "_insert" "blkuc10" "3200,879.28" "1" "1" "0")
(command "_insert" "blkuc10" "3200,878.91" "1" "1" "180")
(command "_insert" "blkuc10" "3200,879.65" "1" "1" "0")
(command "_insert" "blkuc10" "3200,879.28" "1" "1" "180")
(command "_insert" "blkuc10" "3200,880.02" "1" "1" "0")
(command "_insert" "blkuc10" "3200,879.65" "1" "1" "180")
(command "_insert" "blkuc10" "3200,880.39" "1" "1" "0")
(command "_insert" "blkuc10" "3200,880.02" "1" "1" "180")
(command "_insert" "blkuc10" "3200,880.76" "1" "1" "0")
(command "_insert" "blkuc10" "3200,880.39" "1" "1" "180")
(command "_insert" "blkuc10" "3200,881.13" "1" "1" "0")
(command "_insert" "blkuc10" "3200,880.76" "1" "1" "180")
(command "_insert" "blkuc10" "3200,881.5" "1" "1" "0")
(command "_insert" "blkuc10" "3200,881.13" "1" "1" "180")
(command "_insert" "blkuc10" "3200,881.87" "1" "1" "0")
(command "_insert" "blkuc10" "3200,881.5" "1" "1" "180")
(command "_insert" "blkuc10" "3200,882.24" "1" "1" "0")
(command "_insert" "blkuc10" "3200,881.87" "1" "1" "180")
(command "_insert" "blkuc10" "3200,882.61" "1" "1" "0")
(command "_insert" "blkuc10" "3200,882.24" "1" "1" "180")
(command "_insert" "blkuc10" "3200,882.98" "1" "1" "0")
(command "_insert" "blkuc10" "3200,882.61" "1" "1" "180")
(command "_insert" "blkuc10" "3200,883.35" "1" "1" "0")
(command "_insert" "blkuc10" "3200,882.98" "1" "1" "180")
(command "_insert" "blkuc10" "3200,883.72" "1" "1" "0")
(command "_insert" "blkuc10" "3200,883.35" "1" "1" "180")
(command "_insert" "blkuc10" "3200,884.09" "1" "1" "0")
(command "_insert" "blkuc10" "3200,883.72" "1" "1" "180")
(command "_insert" "blkuc10" "3200,884.46" "1" "1" "0")
(command "_insert" "blkuc10" "3200,884.09" "1" "1" "180")
(command "_insert" "blkuc10" "3200,884.83" "1" "1" "0")
(command "_insert" "blkuc10" "3200,884.46" "1" "1" "180")
(command "_insert" "blkuc10" "3200,885.2" "1" "1" "0")
(command "_insert" "blkuc10" "3200,884.83" "1" "1" "180")
(command "_insert" "blkuc10" "3200,885.57" "1" "1" "0")
(command "_insert" "blkuc10" "3200,885.2" "1" "1" "180")
(command "_insert" "blkuc10" "3200,885.94" "1" "1" "0")
(command "_insert" "blkuc10" "3200,885.57" "1" "1" "180")
(command "_insert" "blkuc10" "3200,886.31" "1" "1" "0")
(command "_insert" "blkuc10" "3200,885.94" "1" "1" "180")
(command "_insert" "blkuc10" "3200,886.68" "1" "1" "0")
(command "_insert" "blkuc10" "3200,886.31" "1" "1" "180")
(command "_insert" "blkuc10" "3200,887.05" "1" "1" "0")
(command "_insert" "blkuc10" "3200,886.68" "1" "1" "180")
(command "_insert" "blkuc10" "3200,887.42" "1" "1" "0")
(command "_insert" "blkuc10" "3200,887.05" "1" "1" "180")
(command "_insert" "blkuc10" "3200,887.79" "1" "1" "0")
(command "_insert" "blkuc10" "3200,887.42" "1" "1" "180")
(command "_insert" "blkuc10" "3200,888.16" "1" "1" "0")
(command "_insert" "blkuc10" "3200,887.79" "1" "1" "180")
(command "_insert" "blkuc10" "3200,888.53" "1" "1" "0")
(command "_insert" "blkuc10" "3200,888.16" "1" "1" "180")
(command "_insert" "blkuc10" "3200,888.9" "1" "1" "0")
(command "_insert" "blkuc10" "3200,888.53" "1" "1" "180")
(command "_insert" "blkuc10" "3200,889.27" "1" "1" "0")
(command "_insert" "blkuc10" "3200,888.9" "1" "1" "180")
(command "_insert" "blkuc10" "3200,889.64" "1" "1" "0")
(command "_insert" "blkuc10" "3200,889.27" "1" "1" "180")
(command "_insert" "blkuc10" "3200,890.01" "1" "1" "0")
(command "_insert" "blkuc10" "3200,889.64" "1" "1" "180")
(command "_insert" "blkuc10" "3200,890.38" "1" "1" "0")
(command "_insert" "blkuc10" "3200,890.01" "1" "1" "180")
(command "_insert" "blkuc10" "3200,890.75" "1" "1" "0")
(command "_insert" "blkuc10" "3200,890.38" "1" "1" "180")
(command "_insert" "blkuc10" "3200,891.12" "1" "1" "0")
(command "_insert" "blkuc10" "3200,890.75" "1" "1" "180")
(command "_insert" "blkuc10" "3200,891.49" "1" "1" "0")
(command "_insert" "blkuc10" "3200,891.12" "1" "1" "180")
(command "_insert" "blkuc10" "3200,891.86" "1" "1" "0")
(command "_insert" "blkuc10" "3200,891.49" "1" "1" "180")
(command "_insert" "blkuc10" "3200,892.23" "1" "1" "0")
(command "_insert" "blkuc10" "3200,891.86" "1" "1" "180")
(command "_insert" "blkuc10" "3200,892.6" "1" "1" "0")
(command "_insert" "blkuc10" "3200,892.23" "1" "1" "180")
(command "_insert" "blkuc10" "3200,892.97" "1" "1" "0")
(command "_insert" "blkuc10" "3200,892.6" "1" "1" "180")
(command "_insert" "blkuc10" "3200,893.34" "1" "1" "0")
(command "_insert" "blkuc10" "3200,892.97" "1" "1" "180")
(command "_insert" "blkuc10" "3200,893.71" "1" "1" "0")
(command "_insert" "blkuc10" "3200,893.34" "1" "1" "180")
(command "_insert" "blkuc10" "3200,894.08" "1" "1" "0")
(command "_insert" "blkuc10" "3200,893.71" "1" "1" "180")
(command "_insert" "blkuc10" "3200,894.45" "1" "1" "0")
(command "_insert" "blkuc10" "3200,894.08" "1" "1" "180")
(command "_insert" "blkuc10" "3200,894.82" "1" "1" "0")
(command "_insert" "blkuc10" "3200,894.45" "1" "1" "180")
(command "_insert" "blkuc10" "3200,895.19" "1" "1" "0")
(command "_insert" "blkuc10" "3200,894.82" "1" "1" "180")
(command "_insert" "blkuc10" "3200,895.56" "1" "1" "0")
(command "_insert" "blkuc10" "3200,895.19" "1" "1" "180")
(command "_insert" "blkuc10" "3200,895.93" "1" "1" "0")
(command "_insert" "blkuc10" "3200,895.56" "1" "1" "180")
(command "_insert" "blkuc10" "3200,896.3" "1" "1" "0")
(command "_insert" "blkuc10" "3200,895.93" "1" "1" "180")
(command "_insert" "blkuc10" "3200,896.67" "1" "1" "0")
(command "_insert" "blkuc10" "3200,896.3" "1" "1" "180")
(command "_insert" "blkuc10" "3200,897.04" "1" "1" "0")
(command "_insert" "blkuc10" "3200,896.67" "1" "1" "180")
(command "_insert" "blkuc10" "3200,897.41" "1" "1" "0")
(command "_insert" "blkuc10" "3200,897.04" "1" "1" "180")
(command "_insert" "blkuc10" "3200,897.78" "1" "1" "0")
(command "_insert" "blkuc10" "3200,897.41" "1" "1" "180")
(command "_insert" "blkuc10" "3200,898.15" "1" "1" "0")
(command "_insert" "blkuc10" "3200,897.78" "1" "1" "180")
(command "_insert" "blkuc10" "3200,898.52" "1" "1" "0")
(command "_insert" "blkuc10" "3200,898.15" "1" "1" "180")
(command "_insert" "blkuc10" "3200,898.89" "1" "1" "0")
(command "_insert" "blkuc10" "3200,898.52" "1" "1" "180")
(command "_insert" "blkuc10" "3200,899.26" "1" "1" "0")
(command "_insert" "blkuc10" "3200,898.89" "1" "1" "180")
(command "_insert" "blkuc10" "3200,899.63" "1" "1" "0")
(command "_insert" "blkuc10" "3200,899.26" "1" "1" "180")
(command "_insert" "blkuc10" "3200,900" "1" "1" "0")
(command "_insert" "blkuc10" "3200,899.63" "1" "1" "180")
(command "_insert" "blkuc10" "3200,900.37" "1" "1" "0")
(command "_insert" "blkuc10" "3200,900" "1" "1" "180")
(command "_insert" "blkuc10" "3200,900.74" "1" "1" "0")
(command "_insert" "blkuc10" "3200,900.37" "1" "1" "180")
(command "_insert" "blkuc10" "3200,901.11" "1" "1" "0")
(command "_insert" "blkuc10" "3200,900.74" "1" "1" "180")
(command "_insert" "blkuc10" "3200,901.48" "1" "1" "0")
(command "_insert" "blkuc10" "3200,901.11" "1" "1" "180")
(command "_insert" "blkuc10" "3200,901.85" "1" "1" "0")
(command "_insert" "blkuc10" "3200,901.48" "1" "1" "180")
(command "_insert" "blkuc10" "3200,902.22" "1" "1" "0")
(command "_insert" "blkuc10" "3200,901.85" "1" "1" "180")
(command "_insert" "blkuc10" "3200,902.59" "1" "1" "0")
(command "_insert" "blkuc10" "3200,902.22" "1" "1" "180")
(command "_insert" "blkuc10" "3200,902.96" "1" "1" "0")
(command "_insert" "blkuc10" "3200,902.59" "1" "1" "180")
(command "_insert" "blkuc10" "3200,903.33" "1" "1" "0")
(command "_insert" "blkuc10" "3200,902.96" "1" "1" "180")
(command "_insert" "blkuc10" "3200,903.7" "1" "1" "0")
(command "_insert" "blkuc10" "3200,903.33" "1" "1" "180")
(command "_insert" "blkuc10" "3200,904.07" "1" "1" "0")
(command "_insert" "blkuc10" "3200,903.7" "1" "1" "180")
(command "_insert" "blkuc10" "3200,904.44" "1" "1" "0")
(command "_insert" "blkuc10" "3200,904.07" "1" "1" "180")
(command "_insert" "blkuc10" "3200,904.81" "1" "1" "0")
(command "_insert" "blkuc10" "3200,904.44" "1" "1" "180")
(command "_insert" "blkuc10" "3200,905.18" "1" "1" "0")
(command "_insert" "blkuc10" "3200,904.81" "1" "1" "180")
(command "_insert" "blkuc10" "3200,905.55" "1" "1" "0")
(command "_insert" "blkuc10" "3200,905.18" "1" "1" "180")
(command "_insert" "blkuc10" "3200,905.92" "1" "1" "0")
(command "_insert" "blkuc10" "3200,905.55" "1" "1" "180")
(command "_insert" "blkuc10" "3200,906.29" "1" "1" "0")
(command "_insert" "blkuc10" "3200,905.92" "1" "1" "180")
(command "_insert" "blkuc10" "3200,906.66" "1" "1" "0")
(command "_insert" "blkuc10" "3200,906.29" "1" "1" "180")
(command "_insert" "blkuc10" "3200,907.03" "1" "1" "0")
(command "_insert" "blkuc10" "3200,906.66" "1" "1" "180")
(command "_insert" "blkuc10" "3200,907.4" "1" "1" "0")
(command "_insert" "blkuc10" "3200,907.03" "1" "1" "180")
(command "_insert" "blkuc10" "3200,907.77" "1" "1" "0")
(command "_insert" "blkuc10" "3200,907.4" "1" "1" "180")
(command "_insert" "blkuc10" "3200,908.14" "1" "1" "0")
(command "_insert" "blkuc10" "3200,907.77" "1" "1" "180")
(command "_insert" "blkuc10" "3200,908.51" "1" "1" "0")
(command "_insert" "blkuc10" "3200,908.14" "1" "1" "180")
(command "_insert" "blkuc10" "3200,908.88" "1" "1" "0")
(command "_insert" "blkuc10" "3200,908.51" "1" "1" "180")
(command "_insert" "blkuc10" "3200,909.25" "1" "1" "0")
(command "_insert" "blkuc10" "3200,908.88" "1" "1" "180")
(command "_insert" "blkuc10" "3200,909.62" "1" "1" "0")
(command "_insert" "blkuc10" "3200,909.25" "1" "1" "180")
(command "_insert" "blkuc10" "3200,909.99" "1" "1" "0")
(command "_insert" "blkuc10" "3200,909.62" "1" "1" "180")
(command "_insert" "blkuc10" "3200,910.36" "1" "1" "0")
(command "_insert" "blkuc10" "3200,909.99" "1" "1" "180")
(command "_insert" "blkuc10" "3200,910.73" "1" "1" "0")
(command "_insert" "blkuc10" "3200,910.36" "1" "1" "180")
(command "_insert" "blkuc10" "3200,911.1" "1" "1" "0")
(command "_insert" "blkuc10" "3200,910.73" "1" "1" "180")
(command "_insert" "blkuc10" "3200,911.47" "1" "1" "0")
(command "_insert" "blkuc10" "3200,911.1" "1" "1" "180")
(command "_insert" "blkuc10" "3200,911.84" "1" "1" "0")
(command "_insert" "blkuc10" "3200,911.47" "1" "1" "180")
(command "_insert" "blkuc10" "3200,912.21" "1" "1" "0")
(command "_insert" "blkuc10" "3200,911.84" "1" "1" "180")
(command "_insert" "blkuc10" "3200,912.58" "1" "1" "0")
(command "_insert" "blkuc10" "3200,912.21" "1" "1" "180")
(command "_insert" "blkuc10" "3200,912.95" "1" "1" "0")
(command "_insert" "blkuc10" "3200,912.58" "1" "1" "180")
(command "_insert" "blkuc10" "3200,913.32" "1" "1" "0")
(command "_insert" "blkuc10" "3200,912.95" "1" "1" "180")
(command "_insert" "blkuc10" "3200,913.69" "1" "1" "0")
(command "_insert" "blkuc10" "3200,913.32" "1" "1" "180")
(command "_insert" "blkuc10" "3200,914.06" "1" "1" "0")
(command "_insert" "blkuc10" "3200,913.69" "1" "1" "180")
(command "_insert" "blkuc10" "3200,914.43" "1" "1" "0")
(command "_insert" "blkuc10" "3200,914.06" "1" "1" "180")
(command "_insert" "blkuc10" "3200,914.8" "1" "1" "0")
(command "_insert" "blkuc10" "3200,914.43" "1" "1" "180")
(command "_insert" "blkuc10" "3200,915.17" "1" "1" "0")
(command "_insert" "blkuc10" "3200,914.8" "1" "1" "180")
(command "_insert" "blkuc10" "3200,915.54" "1" "1" "0")
(command "_insert" "blkuc10" "3200,915.17" "1" "1" "180")
(command "_insert" "blkuc10" "3200,915.91" "1" "1" "0")
(command "_insert" "blkuc10" "3200,915.54" "1" "1" "180")
(command "_insert" "blkuc10" "3200,916.28" "1" "1" "0")
(command "_insert" "blkuc10" "3200,915.91" "1" "1" "180")
(command "_insert" "blkuc10" "3200,916.65" "1" "1" "0")
(command "_insert" "blkuc10" "3200,916.28" "1" "1" "180")
(command "_insert" "blkuc10" "3200,917.02" "1" "1" "0")
(command "_insert" "blkuc10" "3200,916.65" "1" "1" "180")
(command "_insert" "blkuc10" "3200,917.39" "1" "1" "0")
(command "_insert" "blkuc10" "3200,917.02" "1" "1" "180")
(command "_insert" "blkuc10" "3200,917.76" "1" "1" "0")
(command "_insert" "blkuc10" "3200,917.39" "1" "1" "180")
(command "_insert" "blkuc10" "3200,918.13" "1" "1" "0")
(command "_insert" "blkuc10" "3200,917.76" "1" "1" "180")
(command "_insert" "blkuc10" "3200,918.5" "1" "1" "0")
(command "_insert" "blkuc10" "3200,918.13" "1" "1" "180")
(command "_insert" "blkuc10" "3200,918.87" "1" "1" "0")
(command "_insert" "blkuc10" "3200,918.5" "1" "1" "180")
(command "_insert" "blkuc10" "3200,919.24" "1" "1" "0")
(command "_insert" "blkuc10" "3200,918.87" "1" "1" "180")
(command "_insert" "blkuc10" "3200,919.61" "1" "1" "0")
(command "_insert" "blkuc10" "3200,919.24" "1" "1" "180")
(command "_insert" "blkuc10" "3200,919.98" "1" "1" "0")
(command "_insert" "blkuc10" "3200,919.61" "1" "1" "180")
(command "_insert" "blkuc10" "3200,920.35" "1" "1" "0")
(command "_insert" "blkuc10" "3200,919.98" "1" "1" "180")
(command "_insert" "blkuc10" "3200,920.72" "1" "1" "0")
(command "_insert" "blkuc10" "3200,920.35" "1" "1" "180")
(command "_insert" "blkuc10" "3200,921.09" "1" "1" "0")
(command "_insert" "blkuc10" "3200,920.72" "1" "1" "180")
(command "_insert" "blkuc10" "3200,921.46" "1" "1" "0")
(command "_insert" "blkuc10" "3200,921.09" "1" "1" "180")
(command "_insert" "blkuc10" "3200,921.83" "1" "1" "0")
(command "_insert" "blkuc10" "3200,921.46" "1" "1" "180")
(command "_insert" "blkuc10" "3200,922.2" "1" "1" "0")
(command "_insert" "blkuc10" "3200,921.83" "1" "1" "180")
(command "_insert" "blkuc10" "3200,922.57" "1" "1" "0")
(command "_insert" "blkuc10" "3200,922.2" "1" "1" "180")
(command "_insert" "blkuc10" "3200,922.94" "1" "1" "0")
(command "_insert" "blkuc10" "3200,922.57" "1" "1" "180")
(command "_insert" "blkuc10" "3200,923.31" "1" "1" "0")
(command "_insert" "blkuc10" "3200,922.94" "1" "1" "180")
(command "_insert" "blkuc10" "3200,923.68" "1" "1" "0")
(command "_insert" "blkuc10" "3200,923.31" "1" "1" "180")
(command "_insert" "blkuc10" "3200,924.05" "1" "1" "0")
(command "_insert" "blkuc10" "3200,923.68" "1" "1" "180")
(command "_insert" "blkuc10" "3200,924.42" "1" "1" "0")
(command "_insert" "blkuc10" "3200,924.05" "1" "1" "180")
(command "_insert" "blkuc10" "3200,924.79" "1" "1" "0")
(command "_insert" "blkuc10" "3200,924.42" "1" "1" "180")
(command "_insert" "blkuc10" "3200,925.16" "1" "1" "0")
(command "_insert" "blkuc10" "3200,924.79" "1" "1" "180")
(command "_insert" "blkuc10" "3200,925.53" "1" "1" "0")
(command "_insert" "blkuc10" "3200,925.16" "1" "1" "180")
(command "_insert" "blkuc10" "3200,925.9" "1" "1" "0")
(command "_insert" "blkuc10" "3200,925.53" "1" "1" "180")
(command "_insert" "blkuc10" "3200,926.27" "1" "1" "0")
(command "_insert" "blkuc10" "3200,925.9" "1" "1" "180")
(command "_insert" "blkuc10" "3200,926.64" "1" "1" "0")
(command "_insert" "blkuc10" "3200,926.27" "1" "1" "180")
(command "_insert" "blkuc10" "3200,927.01" "1" "1" "0")
(command "_insert" "blkuc10" "3200,926.64" "1" "1" "180")
(command "_insert" "blkuc10" "3200,927.38" "1" "1" "0")
(command "_insert" "blkuc10" "3200,927.01" "1" "1" "180")
(command "_insert" "blkuc10" "3200,927.75" "1" "1" "0")
(command "_insert" "blkuc10" "3200,927.38" "1" "1" "180")
(command "_layer" "set" "phccover" "")
(command "_rectangle" "3198.888,933.3" "3201.112,866.7")
(command "_layer" "set" "nitride" "")
(setq phc10 currobj)
(command "_layer" "set" "cover" "")
(command "_rectangle" "3198.888,836.7" "3201.112,963.3")
(command "_layer" "set" "nitride" "")
(command "_layer" "set" "text" "")
(command "_circle" "3197.938,846.7" "0.075")
(command "_circle" "3197.563,846.7" "0.15")
(command "_circle" "3197.188,846.7" "0.075")
(command "_circle" "3196.813,846.7" "0.15")
(command "_circle" "3197.938,848.7" "0.075")
(command "_circle" "3197.563,848.7" "0.075")
(command "_circle" "3197.188,848.7" "0.15")
(command "_circle" "3196.813,848.7" "0.15")
(command "_circle" "3197.938,850.7" "0.075")
(command "_circle" "3197.563,850.7" "0.15")
(command "_circle" "3197.188,850.7" "0.15")
(command "_circle" "3196.813,850.7" "0.15")
(command "_circle" "3197.938,852.7" "0.075")
(command "_circle" "3197.563,852.7" "0.075")
(command "_circle" "3197.188,852.7" "0.075")
(command "_circle" "3196.813,852.7" "0.075")
(command "_circle" "3196.438,852.7" "0.15")
(command "_circle" "3197.938,854.7" "0.075")
(command "_circle" "3197.563,854.7" "0.15")
(command "_circle" "3197.188,854.7" "0.075")
(command "_circle" "3196.813,854.7" "0.075")
(command "_circle" "3196.438,854.7" "0.15")
(command "_circle" "3197.938,856.7" "0.075")
(command "_circle" "3197.563,856.7" "0.075")
(command "_circle" "3197.188,856.7" "0.15")
(command "_circle" "3196.813,856.7" "0.075")
(command "_circle" "3196.438,856.7" "0.15")
(command "_circle" "3197.938,858.7" "0.075")
(command "_circle" "3197.563,858.7" "0.15")
(command "_circle" "3197.188,858.7" "0.15")
(command "_circle" "3196.813,858.7" "0.075")
(command "_circle" "3196.438,858.7" "0.15")
(command "_circle" "3197.938,860.7" "0.075")
(command "_circle" "3197.563,860.7" "0.075")
(command "_circle" "3197.188,860.7" "0.075")
(command "_circle" "3196.813,860.7" "0.15")
(command "_circle" "3196.438,860.7" "0.15")
(command "_circle" "3197.938,862.7" "0.075")
(command "_circle" "3197.563,862.7" "0.15")
(command "_circle" "3197.188,862.7" "0.075")
(command "_circle" "3196.813,862.7" "0.15")
(command "_circle" "3196.438,862.7" "0.15")
(command "_circle" "3197.938,864.7" "0.075")
(command "_circle" "3197.563,864.7" "0.075")
(command "_circle" "3197.188,864.7" "0.15")
(command "_circle" "3196.813,864.7" "0.15")
(command "_circle" "3196.438,864.7" "0.15")
(command "_circle" "3197.938,866.7" "0.075")
(command "_circle" "3197.563,866.7" "0.15")
(command "_circle" "3197.188,866.7" "0.15")
(command "_circle" "3196.813,866.7" "0.15")
(command "_circle" "3196.438,866.7" "0.15")
(command "_circle" "3197.938,868.7" "0.075")
(command "_circle" "3197.563,868.7" "0.075")
(command "_circle" "3197.188,868.7" "0.075")
(command "_circle" "3196.813,868.7" "0.075")
(command "_circle" "3196.438,868.7" "0.075")
(command "_circle" "3196.063,868.7" "0.15")
(command "_circle" "3197.938,870.7" "0.075")
(command "_circle" "3197.563,870.7" "0.15")
(command "_circle" "3197.188,870.7" "0.075")
(command "_circle" "3196.813,870.7" "0.075")
(command "_circle" "3196.438,870.7" "0.075")
(command "_circle" "3196.063,870.7" "0.15")
(command "_circle" "3197.938,872.7" "0.075")
(command "_circle" "3197.563,872.7" "0.075")
(command "_circle" "3197.188,872.7" "0.15")
(command "_circle" "3196.813,872.7" "0.075")
(command "_circle" "3196.438,872.7" "0.075")
(command "_circle" "3196.063,872.7" "0.15")
(command "_circle" "3197.938,874.7" "0.075")
(command "_circle" "3197.563,874.7" "0.15")
(command "_circle" "3197.188,874.7" "0.15")
(command "_circle" "3196.813,874.7" "0.075")
(command "_circle" "3196.438,874.7" "0.075")
(command "_circle" "3196.063,874.7" "0.15")
(command "_circle" "3197.938,876.7" "0.075")
(command "_circle" "3197.563,876.7" "0.075")
(command "_circle" "3197.188,876.7" "0.075")
(command "_circle" "3196.813,876.7" "0.15")
(command "_circle" "3196.438,876.7" "0.075")
(command "_circle" "3196.063,876.7" "0.15")
(command "_circle" "3197.938,878.7" "0.075")
(command "_circle" "3197.563,878.7" "0.15")
(command "_circle" "3197.188,878.7" "0.075")
(command "_circle" "3196.813,878.7" "0.15")
(command "_circle" "3196.438,878.7" "0.075")
(command "_circle" "3196.063,878.7" "0.15")
(command "_circle" "3197.938,880.7" "0.075")
(command "_circle" "3197.563,880.7" "0.075")
(command "_circle" "3197.188,880.7" "0.15")
(command "_circle" "3196.813,880.7" "0.15")
(command "_circle" "3196.438,880.7" "0.075")
(command "_circle" "3196.063,880.7" "0.15")
(command "_circle" "3197.938,882.7" "0.075")
(command "_circle" "3197.563,882.7" "0.15")
(command "_circle" "3197.188,882.7" "0.15")
(command "_circle" "3196.813,882.7" "0.15")
(command "_circle" "3196.438,882.7" "0.075")
(command "_circle" "3196.063,882.7" "0.15")
(command "_circle" "3197.938,884.7" "0.075")
(command "_circle" "3197.563,884.7" "0.075")
(command "_circle" "3197.188,884.7" "0.075")
(command "_circle" "3196.813,884.7" "0.075")
(command "_circle" "3196.438,884.7" "0.15")
(command "_circle" "3196.063,884.7" "0.15")
(command "_circle" "3197.938,886.7" "0.075")
(command "_circle" "3197.563,886.7" "0.15")
(command "_circle" "3197.188,886.7" "0.075")
(command "_circle" "3196.813,886.7" "0.075")
(command "_circle" "3196.438,886.7" "0.15")
(command "_circle" "3196.063,886.7" "0.15")
(command "_circle" "3197.938,888.7" "0.075")
(command "_circle" "3197.563,888.7" "0.075")
(command "_circle" "3197.188,888.7" "0.15")
(command "_circle" "3196.813,888.7" "0.075")
(command "_circle" "3196.438,888.7" "0.15")
(command "_circle" "3196.063,888.7" "0.15")
(command "_circle" "3197.938,890.7" "0.075")
(command "_circle" "3197.563,890.7" "0.15")
(command "_circle" "3197.188,890.7" "0.15")
(command "_circle" "3196.813,890.7" "0.075")
(command "_circle" "3196.438,890.7" "0.15")
(command "_circle" "3196.063,890.7" "0.15")
(command "_circle" "3197.938,892.7" "0.075")
(command "_circle" "3197.563,892.7" "0.075")
(command "_circle" "3197.188,892.7" "0.075")
(command "_circle" "3196.813,892.7" "0.15")
(command "_circle" "3196.438,892.7" "0.15")
(command "_circle" "3196.063,892.7" "0.15")
(command "_circle" "3197.938,894.7" "0.075")
(command "_circle" "3197.563,894.7" "0.15")
(command "_circle" "3197.188,894.7" "0.075")
(command "_circle" "3196.813,894.7" "0.15")
(command "_circle" "3196.438,894.7" "0.15")
(command "_circle" "3196.063,894.7" "0.15")
(command "_circle" "3197.938,896.7" "0.075")
(command "_circle" "3197.563,896.7" "0.075")
(command "_circle" "3197.188,896.7" "0.15")
(command "_circle" "3196.813,896.7" "0.15")
(command "_circle" "3196.438,896.7" "0.15")
(command "_circle" "3196.063,896.7" "0.15")
(command "_circle" "3197.938,898.7" "0.075")
(command "_circle" "3197.563,898.7" "0.15")
(command "_circle" "3197.188,898.7" "0.15")
(command "_circle" "3196.813,898.7" "0.15")
(command "_circle" "3196.438,898.7" "0.15")
(command "_circle" "3196.063,898.7" "0.15")
(command "_circle" "3197.938,900.7" "0.075")
(command "_circle" "3197.563,900.7" "0.075")
(command "_circle" "3197.188,900.7" "0.075")
(command "_circle" "3196.813,900.7" "0.075")
(command "_circle" "3196.438,900.7" "0.075")
(command "_circle" "3196.063,900.7" "0.075")
(command "_circle" "3195.688,900.7" "0.15")
(command "_circle" "3197.938,902.7" "0.075")
(command "_circle" "3197.563,902.7" "0.15")
(command "_circle" "3197.188,902.7" "0.075")
(command "_circle" "3196.813,902.7" "0.075")
(command "_circle" "3196.438,902.7" "0.075")
(command "_circle" "3196.063,902.7" "0.075")
(command "_circle" "3195.688,902.7" "0.15")
(command "_circle" "3197.938,904.7" "0.075")
(command "_circle" "3197.563,904.7" "0.075")
(command "_circle" "3197.188,904.7" "0.15")
(command "_circle" "3196.813,904.7" "0.075")
(command "_circle" "3196.438,904.7" "0.075")
(command "_circle" "3196.063,904.7" "0.075")
(command "_circle" "3195.688,904.7" "0.15")
(command "_circle" "3197.938,906.7" "0.075")
(command "_circle" "3197.563,906.7" "0.15")
(command "_circle" "3197.188,906.7" "0.15")
(command "_circle" "3196.813,906.7" "0.075")
(command "_circle" "3196.438,906.7" "0.075")
(command "_circle" "3196.063,906.7" "0.075")
(command "_circle" "3195.688,906.7" "0.15")
(command "_circle" "3197.938,908.7" "0.075")
(command "_circle" "3197.563,908.7" "0.075")
(command "_circle" "3197.188,908.7" "0.075")
(command "_circle" "3196.813,908.7" "0.15")
(command "_circle" "3196.438,908.7" "0.075")
(command "_circle" "3196.063,908.7" "0.075")
(command "_circle" "3195.688,908.7" "0.15")
(command "_circle" "3197.938,910.7" "0.075")
(command "_circle" "3197.563,910.7" "0.15")
(command "_circle" "3197.188,910.7" "0.075")
(command "_circle" "3196.813,910.7" "0.15")
(command "_circle" "3196.438,910.7" "0.075")
(command "_circle" "3196.063,910.7" "0.075")
(command "_circle" "3195.688,910.7" "0.15")
(command "_circle" "3197.938,912.7" "0.075")
(command "_circle" "3197.563,912.7" "0.075")
(command "_circle" "3197.188,912.7" "0.15")
(command "_circle" "3196.813,912.7" "0.15")
(command "_circle" "3196.438,912.7" "0.075")
(command "_circle" "3196.063,912.7" "0.075")
(command "_circle" "3195.688,912.7" "0.15")
(command "_circle" "3197.938,914.7" "0.075")
(command "_circle" "3197.563,914.7" "0.15")
(command "_circle" "3197.188,914.7" "0.15")
(command "_circle" "3196.813,914.7" "0.15")
(command "_circle" "3196.438,914.7" "0.075")
(command "_circle" "3196.063,914.7" "0.075")
(command "_circle" "3195.688,914.7" "0.15")
(command "_circle" "3197.938,916.7" "0.075")
(command "_circle" "3197.563,916.7" "0.075")
(command "_circle" "3197.188,916.7" "0.075")
(command "_circle" "3196.813,916.7" "0.075")
(command "_circle" "3196.438,916.7" "0.15")
(command "_circle" "3196.063,916.7" "0.075")
(command "_circle" "3195.688,916.7" "0.15")
(command "_circle" "3197.938,918.7" "0.075")
(command "_circle" "3197.563,918.7" "0.15")
(command "_circle" "3197.188,918.7" "0.075")
(command "_circle" "3196.813,918.7" "0.075")
(command "_circle" "3196.438,918.7" "0.15")
(command "_circle" "3196.063,918.7" "0.075")
(command "_circle" "3195.688,918.7" "0.15")
(command "_circle" "3197.938,920.7" "0.075")
(command "_circle" "3197.563,920.7" "0.075")
(command "_circle" "3197.188,920.7" "0.15")
(command "_circle" "3196.813,920.7" "0.075")
(command "_circle" "3196.438,920.7" "0.15")
(command "_circle" "3196.063,920.7" "0.075")
(command "_circle" "3195.688,920.7" "0.15")
(command "_circle" "3197.938,922.7" "0.075")
(command "_circle" "3197.563,922.7" "0.15")
(command "_circle" "3197.188,922.7" "0.15")
(command "_circle" "3196.813,922.7" "0.075")
(command "_circle" "3196.438,922.7" "0.15")
(command "_circle" "3196.063,922.7" "0.075")
(command "_circle" "3195.688,922.7" "0.15")
(command "_circle" "3197.938,924.7" "0.075")
(command "_circle" "3197.563,924.7" "0.075")
(command "_circle" "3197.188,924.7" "0.075")
(command "_circle" "3196.813,924.7" "0.15")
(command "_circle" "3196.438,924.7" "0.15")
(command "_circle" "3196.063,924.7" "0.075")
(command "_circle" "3195.688,924.7" "0.15")
(command "_circle" "3197.938,926.7" "0.075")
(command "_circle" "3197.563,926.7" "0.15")
(command "_circle" "3197.188,926.7" "0.075")
(command "_circle" "3196.813,926.7" "0.15")
(command "_circle" "3196.438,926.7" "0.15")
(command "_circle" "3196.063,926.7" "0.075")
(command "_circle" "3195.688,926.7" "0.15")
(command "_circle" "3197.938,928.7" "0.075")
(command "_circle" "3197.563,928.7" "0.075")
(command "_circle" "3197.188,928.7" "0.15")
(command "_circle" "3196.813,928.7" "0.15")
(command "_circle" "3196.438,928.7" "0.15")
(command "_circle" "3196.063,928.7" "0.075")
(command "_circle" "3195.688,928.7" "0.15")
(command "_circle" "3197.938,930.7" "0.075")
(command "_circle" "3197.563,930.7" "0.15")
(command "_circle" "3197.188,930.7" "0.15")
(command "_circle" "3196.813,930.7" "0.15")
(command "_circle" "3196.438,930.7" "0.15")
(command "_circle" "3196.063,930.7" "0.075")
(command "_circle" "3195.688,930.7" "0.15")
(command "_circle" "3197.938,932.7" "0.075")
(command "_circle" "3197.563,932.7" "0.075")
(command "_circle" "3197.188,932.7" "0.075")
(command "_circle" "3196.813,932.7" "0.075")
(command "_circle" "3196.438,932.7" "0.075")
(command "_circle" "3196.063,932.7" "0.15")
(command "_circle" "3195.688,932.7" "0.15")
(command "_circle" "3197.938,934.7" "0.075")
(command "_circle" "3197.563,934.7" "0.15")
(command "_circle" "3197.188,934.7" "0.075")
(command "_circle" "3196.813,934.7" "0.075")
(command "_circle" "3196.438,934.7" "0.075")
(command "_circle" "3196.063,934.7" "0.15")
(command "_circle" "3195.688,934.7" "0.15")
(command "_circle" "3197.938,936.7" "0.075")
(command "_circle" "3197.563,936.7" "0.075")
(command "_circle" "3197.188,936.7" "0.15")
(command "_circle" "3196.813,936.7" "0.075")
(command "_circle" "3196.438,936.7" "0.075")
(command "_circle" "3196.063,936.7" "0.15")
(command "_circle" "3195.688,936.7" "0.15")
(command "_circle" "3197.938,938.7" "0.075")
(command "_circle" "3197.563,938.7" "0.15")
(command "_circle" "3197.188,938.7" "0.15")
(command "_circle" "3196.813,938.7" "0.075")
(command "_circle" "3196.438,938.7" "0.075")
(command "_circle" "3196.063,938.7" "0.15")
(command "_circle" "3195.688,938.7" "0.15")
(command "_circle" "3197.938,940.7" "0.075")
(command "_circle" "3197.563,940.7" "0.075")
(command "_circle" "3197.188,940.7" "0.075")
(command "_circle" "3196.813,940.7" "0.15")
(command "_circle" "3196.438,940.7" "0.075")
(command "_circle" "3196.063,940.7" "0.15")
(command "_circle" "3195.688,940.7" "0.15")
(command "_circle" "3197.938,942.7" "0.075")
(command "_circle" "3197.563,942.7" "0.15")
(command "_circle" "3197.188,942.7" "0.075")
(command "_circle" "3196.813,942.7" "0.15")
(command "_circle" "3196.438,942.7" "0.075")
(command "_circle" "3196.063,942.7" "0.15")
(command "_circle" "3195.688,942.7" "0.15")
(command "_circle" "3197.938,944.7" "0.075")
(command "_circle" "3197.563,944.7" "0.075")
(command "_circle" "3197.188,944.7" "0.15")
(command "_circle" "3196.813,944.7" "0.15")
(command "_circle" "3196.438,944.7" "0.075")
(command "_circle" "3196.063,944.7" "0.15")
(command "_circle" "3195.688,944.7" "0.15")
(command "_circle" "3197.938,946.7" "0.075")
(command "_circle" "3197.563,946.7" "0.15")
(command "_circle" "3197.188,946.7" "0.15")
(command "_circle" "3196.813,946.7" "0.15")
(command "_circle" "3196.438,946.7" "0.075")
(command "_circle" "3196.063,946.7" "0.15")
(command "_circle" "3195.688,946.7" "0.15")
(command "_circle" "3197.938,948.7" "0.075")
(command "_circle" "3197.563,948.7" "0.075")
(command "_circle" "3197.188,948.7" "0.075")
(command "_circle" "3196.813,948.7" "0.075")
(command "_circle" "3196.438,948.7" "0.15")
(command "_circle" "3196.063,948.7" "0.15")
(command "_circle" "3195.688,948.7" "0.15")
(command "_circle" "3197.938,950.7" "0.075")
(command "_circle" "3197.563,950.7" "0.15")
(command "_circle" "3197.188,950.7" "0.075")
(command "_circle" "3196.813,950.7" "0.075")
(command "_circle" "3196.438,950.7" "0.15")
(command "_circle" "3196.063,950.7" "0.15")
(command "_circle" "3195.688,950.7" "0.15")
(command "_circle" "3197.938,952.7" "0.075")
(command "_circle" "3197.563,952.7" "0.075")
(command "_circle" "3197.188,952.7" "0.15")
(command "_circle" "3196.813,952.7" "0.075")
(command "_circle" "3196.438,952.7" "0.15")
(command "_circle" "3196.063,952.7" "0.15")
(command "_circle" "3195.688,952.7" "0.15")
(command "_circle" "3197.938,954.7" "0.075")
(command "_circle" "3197.563,954.7" "0.15")
(command "_circle" "3197.188,954.7" "0.15")
(command "_circle" "3196.813,954.7" "0.075")
(command "_circle" "3196.438,954.7" "0.15")
(command "_circle" "3196.063,954.7" "0.15")
(command "_circle" "3195.688,954.7" "0.15")
(command "_circle" "3197.938,956.7" "0.075")
(command "_circle" "3197.563,956.7" "0.075")
(command "_circle" "3197.188,956.7" "0.075")
(command "_circle" "3196.813,956.7" "0.15")
(command "_circle" "3196.438,956.7" "0.15")
(command "_circle" "3196.063,956.7" "0.15")
(command "_circle" "3195.688,956.7" "0.15")
(command "_circle" "3197.938,958.7" "0.075")
(command "_circle" "3197.563,958.7" "0.15")
(command "_circle" "3197.188,958.7" "0.075")
(command "_circle" "3196.813,958.7" "0.15")
(command "_circle" "3196.438,958.7" "0.15")
(command "_circle" "3196.063,958.7" "0.15")
(command "_circle" "3195.688,958.7" "0.15")
(command "_circle" "3197.938,960.7" "0.075")
(command "_circle" "3197.563,960.7" "0.075")
(command "_circle" "3197.188,960.7" "0.15")
(command "_circle" "3196.813,960.7" "0.15")
(command "_circle" "3196.438,960.7" "0.15")
(command "_circle" "3196.063,960.7" "0.15")
(command "_circle" "3195.688,960.7" "0.15")
(command "_circle" "3197.938,962.7" "0.075")
(command "_circle" "3197.563,962.7" "0.15")
(command "_circle" "3197.188,962.7" "0.15")
(command "_circle" "3196.813,962.7" "0.15")
(command "_circle" "3196.438,962.7" "0.15")
(command "_circle" "3196.063,962.7" "0.15")
(command "_circle" "3195.688,962.7" "0.15")
(command "_layer" "set" "nitride" "")
(command "_layer" "set" "text" "")
(command-s "_text" "3186.888,963.3" "2" "-90" "a = 370 nm" )
(sssetfirst nil (ssget "_L"))
(if (not (numberp (vl-string-search "Mac" (getvar "platform")))) (c:txtexp))
(command "_layer" "set" "nitride" "")
(command "_layer" "set" "text" "")
(command-s "_text" "3183.888,963.3" "2" "-90" "gap = 250 nm" )
(sssetfirst nil (ssget "_L"))
(if (not (numberp (vl-string-search "Mac" (getvar "platform")))) (c:txtexp))
(command "_layer" "set" "nitride" "")
(command "_layer" "set" "text" "")
(command-s "_text" "3180.888,963.3" "2" "-90" "amplitude = 132 nm" )
(sssetfirst nil (ssget "_L"))
(if (not (numberp (vl-string-search "Mac" (getvar "platform")))) (c:txtexp))
(command "_layer" "set" "nitride" "")
(command "_layer" "set" "text" "")
(command-s "_text" "3177.888,963.3" "2" "-90" "start width = 280 nm" )
(sssetfirst nil (ssget "_L"))
(if (not (numberp (vl-string-search "Mac" (getvar "platform")))) (c:txtexp))
(command "_layer" "set" "nitride" "")
(command "_layer" "set" "text" "")
(command-s "_text" "3174.888,963.3" "2" "-90" "width = 299 nm" )
(sssetfirst nil (ssget "_L"))
(if (not (numberp (vl-string-search "Mac" (getvar "platform")))) (c:txtexp))
(command "_layer" "set" "nitride" "")
(command "_layer" "set" "text" "")
(command-s "_text" "3171.888,963.3" "2" "-90" "taper: 15" )
(sssetfirst nil (ssget "_L"))
(if (not (numberp (vl-string-search "Mac" (getvar "platform")))) (c:txtexp))
(command "_layer" "set" "nitride" "")
(command "_layer" "set" "text" "")
(command-s "_text" "3168.888,963.3" "2" "-90" "nominal: 150" )
(sssetfirst nil (ssget "_L"))
(if (not (numberp (vl-string-search "Mac" (getvar "platform")))) (c:txtexp))
(command "_layer" "set" "nitride" "")
(command "_layer" "set" "indicators" "")
(setq coords (list 
(list 3120.415 940) 
(list 3120.415 920) 
(list 3100.415 900) 
(list 3120.415 880) 
(list 3120.415 860) 
(list 3120.415 900) 
(list 3120.415 887.0711) 
(list 3107.4861 900) 
(list 3120.415 912.9289) 
(list 3120.415 900)))
(apply 'command (append '("pline") coords '("c")))
(command "._fillet" "radius" "1" "._fillet" "P" (entlast))
(setq coords (list 
(list 3279.585 940) 
(list 3279.585 920) 
(list 3299.585 900) 
(list 3279.585 880) 
(list 3279.585 860) 
(list 3279.585 900) 
(list 3279.585 887.0711) 
(list 3292.5139 900) 
(list 3279.585 912.9289) 
(list 3279.585 900)))
(apply 'command (append '("pline") coords '("c")))
(command "._fillet" "radius" "1" "._fillet" "P" (entlast))
(command "_layer" "set" "holes" "")
(command "_circle" "3118.0629,914.1124" "0.5")
(command "_circle" "3115.7109,911.7603" "0.5")
(command "_circle" "3113.3588,909.4083" "0.5")
(command "_circle" "3111.0067,907.0562" "0.5")
(command "_circle" "3108.6547,904.7041" "0.5")
(command "_circle" "3106.3026,902.3521" "0.5")
(command "_circle" "3103.9505,900" "0.5")
(command "_circle" "3106.3026,897.6479" "0.5")
(command "_circle" "3108.6547,895.2959" "0.5")
(command "_circle" "3111.0067,892.9438" "0.5")
(command "_circle" "3113.3588,890.5917" "0.5")
(command "_circle" "3115.7109,888.2397" "0.5")
(command "_circle" "3118.0629,885.8876" "0.5")
(command "_circle" "3281.9371,914.1124" "0.5")
(command "_circle" "3284.2891,911.7603" "0.5")
(command "_circle" "3286.6412,909.4083" "0.5")
(command "_circle" "3288.9933,907.0562" "0.5")
(command "_circle" "3291.3453,904.7041" "0.5")
(command "_circle" "3293.6974,902.3521" "0.5")
(command "_circle" "3296.0495,900" "0.5")
(command "_circle" "3293.6974,897.6479" "0.5")
(command "_circle" "3291.3453,895.2959" "0.5")
(command "_circle" "3288.9933,892.9438" "0.5")
(command "_circle" "3286.6412,890.5917" "0.5")
(command "_circle" "3284.2891,888.2397" "0.5")
(command "_circle" "3281.9371,885.8876" "0.5")
(command "_layer" "set" "nitride" "")
(command "_block" "blkcoupler10" "3200,900" coupler10 "")
(command "_insert" "blkcoupler10" "3200,900" "1" "1" "0")
(command "_insert" "blkcoupler10" "3200,900" "1" "1" "180")
(command "_block" "blksinglenanobeam10" "3200,900" singlenanobeam10 "")
(command "_insert" "blksinglenanobeam10" "3200,900" "1" "1" "0")
(command "_insert" "blksinglenanobeam10" "3200,900" "1" "1" "180")
(command "_block" "blkanglednodearray10" "3200,900" anglednodearray10 "")
(command "_insert" "blkanglednodearray10" "3200,900" "1" "1" "0")
(command "_insert" "blkanglednodearray10" "3200,900" "1" "1" "180")
(command "_block" "blkcooledsinglenanobeam10" "3200,900" cooledsinglenanobeam10 "")
(command "_insert" "blkcooledsinglenanobeam10" "3200,900" "1" "1" "0")
(command "_insert" "blkcooledsinglenanobeam10" "3200,900" "1" "1" "180")
(command "_block" "blkyjunction10" "3200,900" yjunction10 "")
(command "_insert" "blkyjunction10" "3200,900" "1" "1" "0")
(command "_insert" "blkyjunction10" "3200,900" "1" "1" "180")
; DRAWING BULGING VEE GROOVE
(command "_layer" "set" "vgroove" "")
(setq coords (list 
(list 3125.415 -605) 
(list 3125.415 0) 
(list 3125.415 0) 
(list 3125.415 1800) 
(list 3125.415 1800) 
(list 3125.415 2405) 
(list 3274.585 2405) 
(list 3274.585 1800) 
(list 3274.585 1800) 
(list 3274.585 0) 
(list 3274.585 0) 
(list 3274.585 -605)))
(apply 'command (append '("pline") coords '("c")))
(command "._fillet" "radius" "0" "._fillet" "P" (entlast))
(command "_layer" "set" "window" "")
(command "_rectangle" "3125.415,-1935" "3274.585,-600")
(command "_rectangle" "3125.415,2400" "3274.585,5300")
(command "_layer" "set" "grid" "")
(command "_rectangle" "3126.415,-1934" "3149.9433,-1909.2133")
(command "_array" "last" "" "R" "75" "3" "25.7867" "24.5283")
(command "_rectangle" "3201,-1934" "3224.5283,-1909.2133")
(command "_array" "last" "" "R" "75" "3" "25.7867" "24.5283")
(command "_rectangle" "3126.415,1" "3149.9433,25.7")
(command "_array" "last" "" "R" "70" "3" "25.7" "24.5283")
(command "_rectangle" "3201,1" "3224.5283,25.7")
(command "_array" "last" "" "R" "70" "3" "25.7" "24.5283")
(command "_rectangle" "3126.415,1801" "3149.9433,1825.9185")
(command "_array" "last" "" "R" "135" "3" "25.9185" "24.5283")
(command "_rectangle" "3201,1801" "3224.5283,1825.9185")
(command "_array" "last" "" "R" "135" "3" "25.9185" "24.5283")
(command "_layer" "set" "vgrooveFDA" "")
(command "_rectangle" "3274.585,-2233" "3125.415,-1933")
(command "_layer" "set" "nitride" "")
(command "_layer" "set" "holes" "")
(command "_circle" "3277.085,331.5" "0.5")
(command "_array" "last" "" "R" "379" "1" "3" "2.5")
(command "_circle" "3122.915,331.5" "0.5")
(command "_array" "last" "" "R" "379" "1" "3" "-2.5")
(command "_layer" "set" "nitride" "")
(command "_layer" "set" "window" "")
(command "_layer" "set" "window" "")
(command "_rectangle" "3279.585,0" "3440.415,1800")
(command "._fillet" "radius" "20" "._fillet" "P" (entlast))
(command "_layer" "set" "grid" "")
(command "_rectangle" "3280.585,1" "3302.4179,25.7")
(command "_array" "last" "" "R" "70" "7" "25.7" "22.8329")
(command "_layer" "set" "nitride" "")
; DRAWING REGION LAYER
(command "_layer" "set" "regionLayer10" "")
(command "_rectangle" "3120,-460" "3280,2260")
(command "_layer" "set" "nitride" "")
(setq coupler10 nil)
(setq singlenanobeam10 nil)
(setq anglednodearray10 nil)
(setq cooledsinglenanobeam10 nil)
(setq yjunction10 nil)
; DEVICE #11
(command "_layer" "set" "window" "")
(command "_circle" "3432.915,-415" "5")
(command "_circle" "3432.915,-402.5" "5")
(command "_circle" "3432.915,-390" "5")
(command "_circle" "3432.915,-377.5" "5")
(command "_circle" "3420.415,-415" "5")
(command "_circle" "3420.415,-402.5" "5")
(command "_circle" "3420.415,-390" "5")
(command "_circle" "3420.415,-377.5" "5")
(command "_circle" "3407.915,-415" "5")
(command "_circle" "3407.915,-402.5" "5")
(command "_circle" "3407.915,-390" "5")
(command "_layer" "set" "nitride" "")
(setq currobj nil)
(setq currobj (ssadd))
; DRAWING COUPLER
(setq coords (list 
(list 3520.0615 -415) 
(list 3520.0615 -413) 
(list 3593.585 -413) 
(list 3593.585 -413) 
(list 3593.9677 -413.0761) 
(list 3594.2921 -413.2929) 
(list 3594.5089 -413.6173) 
(list 3594.585 -414) 
(list 3594.585 -411.8) 
(list 3594.585 -411.8) 
(list 3594.5089 -412.1827) 
(list 3594.2921 -412.5071) 
(list 3593.9677 -412.7239) 
(list 3593.585 -412.8) 
(list 3520.0615 -412.8) 
(list 3520.0615 -410.8) 
(list 3519.9385 -410.8) 
(list 3519.9385 -412.8) 
(list 3446.415 -412.8) 
(list 3446.0323 -412.7239) 
(list 3445.7079 -412.5071) 
(list 3445.4911 -412.1827) 
(list 3445.415 -411.8) 
(list 3445.415 -411.8) 
(list 3445.415 -414) 
(list 3445.4911 -413.6173) 
(list 3445.7079 -413.2929) 
(list 3446.0323 -413.0761) 
(list 3446.415 -413) 
(list 3446.415 -413) 
(list 3519.9385 -413) 
(list 3519.9385 -415)))
(apply 'command (append '("pline") coords '("c")))
(setq currobj (ssadd (entlast) currobj))
(command "._fillet" "radius" "0.3" "._fillet" "P" (entlast))
(command "_layer" "set" "holes" "")
(command "_circle" "3520,-412.9" "0.113")
(setq currobj (ssadd (entlast) currobj))
(command "_layer" "set" "nitride" "")
(command "_layer" "set" "text" "")
(command "_circle" "3519.2,-415" "0.075")
(command "_circle" "3519.2,-414.7" "0.075")
(command "_circle" "3519.2,-414.4" "0.075")
(command "_circle" "3518.9,-415" "0.075")
(command "_circle" "3518.9,-414.7" "0.075")
(command "_circle" "3518.9,-414.4" "0.075")
(command "_circle" "3518.6,-415" "0.075")
(command "_circle" "3518.6,-414.7" "0.075")
(command "_circle" "3518.6,-414.4" "0.075")
(command "_layer" "set" "nitride" "")
(command "_layer" "set" "prebias" "")
(command "_rectangle" "3445.415,-414" "3594.585,-411.8")
(setq currobj (ssadd (entlast) currobj))
(command "_rectangle" "3519.9385,-415" "3520.0615,-410.8")
(setq currobj (ssadd (entlast) currobj))
(command "_layer" "set" "nitride" "")
(setq coupler11 currobj)
(setq currobj nil)
(setq currobj (ssadd))
; DRAWING SINGLE NANOBEAM
(setq coords (list 
(list 3520.0615 -410.8) 
(list 3520.0615 -409.1417) 
(list 3520.0615 -407.4833) 
(list 3520.0615 -405.825) 
(list 3520.0615 -404.1667) 
(list 3520.0615 -402.5083) 
(list 3520.0615 -400.85) 
(list 3520.0615 -399.1917) 
(list 3520.0615 -397.5333) 
(list 3520.0616 -395.875) 
(list 3520.0616 -394.2167) 
(list 3520.0616 -392.5583) 
(list 3520.0616 -390.9) 
(list 3520.0617 -389.2417) 
(list 3520.0617 -387.5833) 
(list 3520.0617 -385.925) 
(list 3520.0618 -384.2667) 
(list 3520.0619 -382.6083) 
(list 3520.0619 -380.95) 
(list 3520.062 -379.2917) 
(list 3520.0621 -377.6333) 
(list 3520.0622 -375.975) 
(list 3520.0623 -374.3167) 
(list 3520.0624 -372.6583) 
(list 3520.0625 -371) 
(list 3520.0626 -369.3417) 
(list 3520.0628 -367.6833) 
(list 3520.0629 -366.025) 
(list 3520.0631 -364.3667) 
(list 3520.0632 -362.7083) 
(list 3520.0634 -361.05) 
(list 3520.0636 -359.3917) 
(list 3520.0638 -357.7333) 
(list 3520.0641 -356.075) 
(list 3520.0643 -354.4167) 
(list 3520.0646 -352.7583) 
(list 3520.0648 -351.1) 
(list 3520.0651 -349.4417) 
(list 3520.0654 -347.7833) 
(list 3520.0657 -346.125) 
(list 3520.0661 -344.4667) 
(list 3520.0664 -342.8083) 
(list 3520.0668 -341.15) 
(list 3520.0672 -339.4917) 
(list 3520.0676 -337.8333) 
(list 3520.068 -336.175) 
(list 3520.0685 -334.5167) 
(list 3520.0689 -332.8583) 
(list 3520.0694 -331.2) 
(list 3520.0699 -329.5417) 
(list 3520.0704 -327.8833) 
(list 3520.071 -326.225) 
(list 3520.0715 -324.5667) 
(list 3520.0721 -322.9083) 
(list 3520.0728 -321.25) 
(list 3520.0734 -319.5917) 
(list 3520.0741 -317.9333) 
(list 3520.0747 -316.275) 
(list 3520.0754 -314.6167) 
(list 3520.0762 -312.9583) 
(list 3520.0769 -311.3) 
(list 3520.0777 -309.6417) 
(list 3520.0785 -307.9833) 
(list 3520.0794 -306.325) 
(list 3520.0802 -304.6667) 
(list 3520.0811 -303.0083) 
(list 3520.082 -301.35) 
(list 3520.083 -299.6917) 
(list 3520.084 -298.0333) 
(list 3520.085 -296.375) 
(list 3520.086 -294.7167) 
(list 3520.0871 -293.0583) 
(list 3520.0882 -291.4) 
(list 3520.0893 -289.7417) 
(list 3520.0905 -288.0833) 
(list 3520.0917 -286.425) 
(list 3520.0929 -284.7667) 
(list 3520.0941 -283.1083) 
(list 3520.0954 -281.45) 
(list 3520.0967 -279.7917) 
(list 3520.0981 -278.1333) 
(list 3520.0995 -276.475) 
(list 3520.1009 -274.8167) 
(list 3520.1024 -273.1583) 
(list 3520.1039 -271.5) 
(list 3520.1054 -269.8417) 
(list 3520.107 -268.1833) 
(list 3520.1086 -266.525) 
(list 3520.1102 -264.8667) 
(list 3520.1119 -263.2083) 
(list 3520.1136 -261.55) 
(list 3520.1154 -259.8917) 
(list 3520.1172 -258.2333) 
(list 3520.119 -256.575) 
(list 3520.1209 -254.9167) 
(list 3520.1228 -253.2583) 
(list 3520.1247 -251.6) 
(list 3520.1267 -249.9417) 
(list 3520.1288 -248.2833) 
(list 3520.1308 -246.625) 
(list 3520.133 -244.9667) 
(list 3520.1351 -243.3083) 
(list 3520.1373 -241.65) 
(list 3520.1396 -239.9917) 
(list 3520.1419 -238.3333) 
(list 3520.1442 -236.675) 
(list 3520.1466 -235.0167) 
(list 3520.1491 -233.3583) 
(list 3520.1515 -231.7) 
(list 3520.1541 -230.0417) 
(list 3520.1566 -228.3833) 
(list 3520.1592 -226.725) 
(list 3520.1619 -225.0667) 
(list 3520.1646 -223.4083) 
(list 3520.1674 -221.75) 
(list 3520.1702 -220.0917) 
(list 3520.1731 -218.4333) 
(list 3520.176 -216.775) 
(list 3520.1789 -215.1167) 
(list 3520.1819 -213.4583) 
(list 3520.185 -211.8) 
(list 3519.815 -211.8) 
(list 3519.8181 -213.4583) 
(list 3519.8211 -215.1167) 
(list 3519.824 -216.775) 
(list 3519.8269 -218.4333) 
(list 3519.8298 -220.0917) 
(list 3519.8326 -221.75) 
(list 3519.8354 -223.4083) 
(list 3519.8381 -225.0667) 
(list 3519.8408 -226.725) 
(list 3519.8434 -228.3833) 
(list 3519.8459 -230.0417) 
(list 3519.8485 -231.7) 
(list 3519.8509 -233.3583) 
(list 3519.8534 -235.0167) 
(list 3519.8558 -236.675) 
(list 3519.8581 -238.3333) 
(list 3519.8604 -239.9917) 
(list 3519.8627 -241.65) 
(list 3519.8649 -243.3083) 
(list 3519.867 -244.9667) 
(list 3519.8692 -246.625) 
(list 3519.8712 -248.2833) 
(list 3519.8733 -249.9417) 
(list 3519.8753 -251.6) 
(list 3519.8772 -253.2583) 
(list 3519.8791 -254.9167) 
(list 3519.881 -256.575) 
(list 3519.8828 -258.2333) 
(list 3519.8846 -259.8917) 
(list 3519.8864 -261.55) 
(list 3519.8881 -263.2083) 
(list 3519.8898 -264.8667) 
(list 3519.8914 -266.525) 
(list 3519.893 -268.1833) 
(list 3519.8946 -269.8417) 
(list 3519.8961 -271.5) 
(list 3519.8976 -273.1583) 
(list 3519.8991 -274.8167) 
(list 3519.9005 -276.475) 
(list 3519.9019 -278.1333) 
(list 3519.9033 -279.7917) 
(list 3519.9046 -281.45) 
(list 3519.9059 -283.1083) 
(list 3519.9071 -284.7667) 
(list 3519.9083 -286.425) 
(list 3519.9095 -288.0833) 
(list 3519.9107 -289.7417) 
(list 3519.9118 -291.4) 
(list 3519.9129 -293.0583) 
(list 3519.914 -294.7167) 
(list 3519.915 -296.375) 
(list 3519.916 -298.0333) 
(list 3519.917 -299.6917) 
(list 3519.918 -301.35) 
(list 3519.9189 -303.0083) 
(list 3519.9198 -304.6667) 
(list 3519.9206 -306.325) 
(list 3519.9215 -307.9833) 
(list 3519.9223 -309.6417) 
(list 3519.9231 -311.3) 
(list 3519.9238 -312.9583) 
(list 3519.9246 -314.6167) 
(list 3519.9253 -316.275) 
(list 3519.9259 -317.9333) 
(list 3519.9266 -319.5917) 
(list 3519.9272 -321.25) 
(list 3519.9279 -322.9083) 
(list 3519.9285 -324.5667) 
(list 3519.929 -326.225) 
(list 3519.9296 -327.8833) 
(list 3519.9301 -329.5417) 
(list 3519.9306 -331.2) 
(list 3519.9311 -332.8583) 
(list 3519.9315 -334.5167) 
(list 3519.932 -336.175) 
(list 3519.9324 -337.8333) 
(list 3519.9328 -339.4917) 
(list 3519.9332 -341.15) 
(list 3519.9336 -342.8083) 
(list 3519.9339 -344.4667) 
(list 3519.9343 -346.125) 
(list 3519.9346 -347.7833) 
(list 3519.9349 -349.4417) 
(list 3519.9352 -351.1) 
(list 3519.9354 -352.7583) 
(list 3519.9357 -354.4167) 
(list 3519.9359 -356.075) 
(list 3519.9362 -357.7333) 
(list 3519.9364 -359.3917) 
(list 3519.9366 -361.05) 
(list 3519.9368 -362.7083) 
(list 3519.9369 -364.3667) 
(list 3519.9371 -366.025) 
(list 3519.9372 -367.6833) 
(list 3519.9374 -369.3417) 
(list 3519.9375 -371) 
(list 3519.9376 -372.6583) 
(list 3519.9377 -374.3167) 
(list 3519.9378 -375.975) 
(list 3519.9379 -377.6333) 
(list 3519.938 -379.2917) 
(list 3519.9381 -380.95) 
(list 3519.9381 -382.6083) 
(list 3519.9382 -384.2667) 
(list 3519.9383 -385.925) 
(list 3519.9383 -387.5833) 
(list 3519.9383 -389.2417) 
(list 3519.9384 -390.9) 
(list 3519.9384 -392.5583) 
(list 3519.9384 -394.2167) 
(list 3519.9384 -395.875) 
(list 3519.9385 -397.5333) 
(list 3519.9385 -399.1917) 
(list 3519.9385 -400.85) 
(list 3519.9385 -402.5083) 
(list 3519.9385 -404.1667) 
(list 3519.9385 -405.825) 
(list 3519.9385 -407.4833) 
(list 3519.9385 -409.1417) 
(list 3519.9385 -410.8)))
(apply 'command (append '("pline") coords '("c")))
(setq currobj (ssadd (entlast) currobj))
(command "_layer" "set" "prebias" "")
(command "_rectangle" "3519.815,-410.8" "3520.185,-211.8")
(setq currobj (ssadd (entlast) currobj))
(command "_layer" "set" "nitride" "")
(setq singlenanobeam11 currobj)
(setq currobj nil)
(setq currobj (ssadd))
; DRAWING NODE ARRAY
(setq coords (list 
(list 3520.185 -211.8) 
(list 3520.5625 -201.8) 
(list 3520.5625 -201.8) 
(list 3520.5625 -200.8) 
(list 3594.585 -212.6864) 
(list 3594.585 -207.7434) 
(list 3520.5625 -197.357) 
(list 3520.5625 -196.357) 
(list 3520.5625 -196.357) 
(list 3520.2625 -186.357) 
(list 3519.7375 -186.357) 
(list 3519.4375 -196.357) 
(list 3519.4375 -196.357) 
(list 3519.4375 -197.357) 
(list 3445.415 -207.7434) 
(list 3445.415 -212.6864) 
(list 3519.4375 -200.8) 
(list 3519.4375 -201.8) 
(list 3519.4375 -201.8) 
(list 3519.815 -211.8)))
(apply 'command (append '("pline") coords '("c")))
(setq currobj (ssadd (entlast) currobj))
(command "_layer" "set" "prebias" "")
(setq coords (list 
(list 3519.4375 -212.6864) 
(list 3519.4375 -200.8) 
(list 3445.415 -212.6864) 
(list 3445.415 -207.7434) 
(list 3519.4375 -197.357) 
(list 3519.4375 -186.357) 
(list 3520.5625 -186.357) 
(list 3520.5625 -197.357) 
(list 3594.585 -207.7434) 
(list 3594.585 -212.6864) 
(list 3520.5625 -200.8) 
(list 3520.5625 -212.6864)))
(apply 'command (append '("pline") coords '("c")))
(setq currobj (ssadd (entlast) currobj))
(command "_layer" "set" "nitride" "")
(command "_layer" "set" "fda1" "")
(setq coords (list 
(list 3520.5625 -200.657) 
(list 3594.585 -212.5434) 
(list 3594.585 -212.3664) 
(list 3520.5625 -200.58)))
(apply 'command (append '("pline") coords '("c")))
(setq currobj (ssadd (entlast) currobj))
(setq coords (list 
(list 3520.5625 -200.437) 
(list 3594.585 -212.2234) 
(list 3594.585 -212.0464) 
(list 3520.5625 -200.36)))
(apply 'command (append '("pline") coords '("c")))
(setq currobj (ssadd (entlast) currobj))
(setq coords (list 
(list 3520.5625 -200.217) 
(list 3594.585 -211.9034) 
(list 3594.585 -211.7264) 
(list 3520.5625 -200.14)))
(apply 'command (append '("pline") coords '("c")))
(setq currobj (ssadd (entlast) currobj))
(setq coords (list 
(list 3520.5625 -199.997) 
(list 3594.585 -211.5834) 
(list 3594.585 -211.4064) 
(list 3520.5625 -199.92)))
(apply 'command (append '("pline") coords '("c")))
(setq currobj (ssadd (entlast) currobj))
(setq coords (list 
(list 3520.5625 -199.777) 
(list 3594.585 -211.2634) 
(list 3594.585 -211.0864) 
(list 3520.5625 -199.7)))
(apply 'command (append '("pline") coords '("c")))
(setq currobj (ssadd (entlast) currobj))
(setq coords (list 
(list 3520.5625 -199.557) 
(list 3594.585 -210.9434) 
(list 3594.585 -210.7664) 
(list 3520.5625 -199.48)))
(apply 'command (append '("pline") coords '("c")))
(setq currobj (ssadd (entlast) currobj))
(setq coords (list 
(list 3520.5625 -199.337) 
(list 3594.585 -210.6234) 
(list 3594.585 -210.4464) 
(list 3520.5625 -199.26)))
(apply 'command (append '("pline") coords '("c")))
(setq currobj (ssadd (entlast) currobj))
(setq coords (list 
(list 3520.5625 -199.117) 
(list 3594.585 -210.3034) 
(list 3594.585 -210.1264) 
(list 3520.5625 -199.04)))
(apply 'command (append '("pline") coords '("c")))
(setq currobj (ssadd (entlast) currobj))
(setq coords (list 
(list 3520.5625 -198.897) 
(list 3594.585 -209.9834) 
(list 3594.585 -209.8064) 
(list 3520.5625 -198.82)))
(apply 'command (append '("pline") coords '("c")))
(setq currobj (ssadd (entlast) currobj))
(setq coords (list 
(list 3520.5625 -198.677) 
(list 3594.585 -209.6634) 
(list 3594.585 -209.4864) 
(list 3520.5625 -198.6)))
(apply 'command (append '("pline") coords '("c")))
(setq currobj (ssadd (entlast) currobj))
(setq coords (list 
(list 3520.5625 -198.457) 
(list 3594.585 -209.3434) 
(list 3594.585 -209.1664) 
(list 3520.5625 -198.38)))
(apply 'command (append '("pline") coords '("c")))
(setq currobj (ssadd (entlast) currobj))
(setq coords (list 
(list 3520.5625 -198.237) 
(list 3594.585 -209.0234) 
(list 3594.585 -208.8464) 
(list 3520.5625 -198.16)))
(apply 'command (append '("pline") coords '("c")))
(setq currobj (ssadd (entlast) currobj))
(setq coords (list 
(list 3520.5625 -198.017) 
(list 3594.585 -208.7034) 
(list 3594.585 -208.5264) 
(list 3520.5625 -197.94)))
(apply 'command (append '("pline") coords '("c")))
(setq currobj (ssadd (entlast) currobj))
(setq coords (list 
(list 3520.5625 -197.797) 
(list 3594.585 -208.3834) 
(list 3594.585 -208.2064) 
(list 3520.5625 -197.72)))
(apply 'command (append '("pline") coords '("c")))
(setq currobj (ssadd (entlast) currobj))
(setq coords (list 
(list 3520.5625 -197.577) 
(list 3594.585 -208.0634) 
(list 3594.585 -207.8864) 
(list 3520.5625 -197.5)))
(apply 'command (append '("pline") coords '("c")))
(setq currobj (ssadd (entlast) currobj))
(setq coords (list 
(list 3519.4375 -197.5) 
(list 3445.415 -207.8864) 
(list 3445.415 -208.0634) 
(list 3519.4375 -197.577)))
(apply 'command (append '("pline") coords '("c")))
(setq currobj (ssadd (entlast) currobj))
(setq coords (list 
(list 3519.4375 -197.72) 
(list 3445.415 -208.2064) 
(list 3445.415 -208.3834) 
(list 3519.4375 -197.797)))
(apply 'command (append '("pline") coords '("c")))
(setq currobj (ssadd (entlast) currobj))
(setq coords (list 
(list 3519.4375 -197.94) 
(list 3445.415 -208.5264) 
(list 3445.415 -208.7034) 
(list 3519.4375 -198.017)))
(apply 'command (append '("pline") coords '("c")))
(setq currobj (ssadd (entlast) currobj))
(setq coords (list 
(list 3519.4375 -198.16) 
(list 3445.415 -208.8464) 
(list 3445.415 -209.0234) 
(list 3519.4375 -198.237)))
(apply 'command (append '("pline") coords '("c")))
(setq currobj (ssadd (entlast) currobj))
(setq coords (list 
(list 3519.4375 -198.38) 
(list 3445.415 -209.1664) 
(list 3445.415 -209.3434) 
(list 3519.4375 -198.457)))
(apply 'command (append '("pline") coords '("c")))
(setq currobj (ssadd (entlast) currobj))
(setq coords (list 
(list 3519.4375 -198.6) 
(list 3445.415 -209.4864) 
(list 3445.415 -209.6634) 
(list 3519.4375 -198.677)))
(apply 'command (append '("pline") coords '("c")))
(setq currobj (ssadd (entlast) currobj))
(setq coords (list 
(list 3519.4375 -198.82) 
(list 3445.415 -209.8064) 
(list 3445.415 -209.9834) 
(list 3519.4375 -198.897)))
(apply 'command (append '("pline") coords '("c")))
(setq currobj (ssadd (entlast) currobj))
(setq coords (list 
(list 3519.4375 -199.04) 
(list 3445.415 -210.1264) 
(list 3445.415 -210.3034) 
(list 3519.4375 -199.117)))
(apply 'command (append '("pline") coords '("c")))
(setq currobj (ssadd (entlast) currobj))
(setq coords (list 
(list 3519.4375 -199.26) 
(list 3445.415 -210.4464) 
(list 3445.415 -210.6234) 
(list 3519.4375 -199.337)))
(apply 'command (append '("pline") coords '("c")))
(setq currobj (ssadd (entlast) currobj))
(setq coords (list 
(list 3519.4375 -199.48) 
(list 3445.415 -210.7664) 
(list 3445.415 -210.9434) 
(list 3519.4375 -199.557)))
(apply 'command (append '("pline") coords '("c")))
(setq currobj (ssadd (entlast) currobj))
(setq coords (list 
(list 3519.4375 -199.7) 
(list 3445.415 -211.0864) 
(list 3445.415 -211.2634) 
(list 3519.4375 -199.777)))
(apply 'command (append '("pline") coords '("c")))
(setq currobj (ssadd (entlast) currobj))
(setq coords (list 
(list 3519.4375 -199.92) 
(list 3445.415 -211.4064) 
(list 3445.415 -211.5834) 
(list 3519.4375 -199.997)))
(apply 'command (append '("pline") coords '("c")))
(setq currobj (ssadd (entlast) currobj))
(setq coords (list 
(list 3519.4375 -200.14) 
(list 3445.415 -211.7264) 
(list 3445.415 -211.9034) 
(list 3519.4375 -200.217)))
(apply 'command (append '("pline") coords '("c")))
(setq currobj (ssadd (entlast) currobj))
(setq coords (list 
(list 3519.4375 -200.36) 
(list 3445.415 -212.0464) 
(list 3445.415 -212.2234) 
(list 3519.4375 -200.437)))
(apply 'command (append '("pline") coords '("c")))
(setq currobj (ssadd (entlast) currobj))
(setq coords (list 
(list 3519.4375 -200.58) 
(list 3445.415 -212.3664) 
(list 3445.415 -212.5434) 
(list 3519.4375 -200.657)))
(apply 'command (append '("pline") coords '("c")))
(setq currobj (ssadd (entlast) currobj))
(command "_layer" "set" "nitride" "")
(command "_layer" "set" "text" "")
(command "_circle" "3518.985,-211.8" "0.075")
(command "_circle" "3518.985,-211.5" "0.075")
(command "_circle" "3518.985,-211.2" "0.075")
(command "_circle" "3518.985,-210.9" "0.075")
(command "_circle" "3518.985,-210.6" "0.075")
(command "_circle" "3518.685,-211.8" "0.075")
(command "_circle" "3518.685,-211.5" "0.075")
(command "_circle" "3518.685,-211.2" "0.075")
(command "_circle" "3518.685,-210.9" "0.075")
(command "_circle" "3518.685,-210.6" "0.075")
(command "_circle" "3518.385,-211.8" "0.075")
(command "_circle" "3518.385,-211.5" "0.075")
(command "_circle" "3518.385,-211.2" "0.075")
(command "_circle" "3518.385,-210.9" "0.075")
(command "_circle" "3518.385,-210.6" "0.075")
(command "_circle" "3518.085,-211.8" "0.075")
(command "_circle" "3518.085,-211.5" "0.075")
(command "_circle" "3518.085,-211.2" "0.075")
(command "_circle" "3518.085,-210.9" "0.075")
(command "_circle" "3518.085,-210.6" "0.075")
(command "_circle" "3517.785,-211.8" "0.075")
(command "_circle" "3517.785,-211.5" "0.075")
(command "_circle" "3517.785,-211.2" "0.075")
(command "_circle" "3517.785,-210.9" "0.075")
(command "_circle" "3517.785,-210.6" "0.075")
(command "_layer" "set" "nitride" "")
(setq anglednodearray11 currobj)
(setq currobj nil)
(setq currobj (ssadd))
; DRAWING COOLED SINGLE NANOBEAM
(setq coords (list 
(list 3520.2625 -186.357) 
(list 3520.2625 -181.357) 
(list 3519.7375 -181.357) 
(list 3519.7375 -186.357)))
(apply 'command (append '("pline") coords '("c")))
(setq currobj (ssadd (entlast) currobj))
(command "_layer" "set" "prebias" "")
(command "_rectangle" "3519.7375,-186.357" "3520.2625,-181.357")
(setq currobj (ssadd (entlast) currobj))
(command "_layer" "set" "nitride" "")
(setq coords (list 
(list 3520.2625 -181.357) 
(list 3520.5625 -171.357) 
(list 3520.5625 -171.357) 
(list 3520.5625 -170.357) 
(list 3594.585 -171.107) 
(list 3594.585 -166.164) 
(list 3520.5625 -166.914) 
(list 3520.5625 -165.914) 
(list 3520.5625 -165.914) 
(list 3520.2625 -155.914) 
(list 3519.7375 -155.914) 
(list 3519.4375 -165.914) 
(list 3519.4375 -165.914) 
(list 3519.4375 -166.914) 
(list 3445.415 -166.164) 
(list 3445.415 -171.107) 
(list 3519.4375 -170.357) 
(list 3519.4375 -171.357) 
(list 3519.4375 -171.357) 
(list 3519.7375 -181.357)))
(apply 'command (append '("pline") coords '("c")))
(setq currobj (ssadd (entlast) currobj))
(command "_layer" "set" "prebias" "")
(setq coords (list 
(list 3519.4375 -181.357) 
(list 3519.4375 -170.357) 
(list 3445.415 -171.107) 
(list 3445.415 -166.164) 
(list 3519.4375 -166.914) 
(list 3519.4375 -155.914) 
(list 3520.5625 -155.914) 
(list 3520.5625 -166.914) 
(list 3594.585 -166.164) 
(list 3594.585 -171.107) 
(list 3520.5625 -170.357) 
(list 3520.5625 -181.357)))
(apply 'command (append '("pline") coords '("c")))
(setq currobj (ssadd (entlast) currobj))
(command "_layer" "set" "nitride" "")
(command "_layer" "set" "fda1" "")
(setq coords (list 
(list 3520.5625 -170.214) 
(list 3594.585 -170.964) 
(list 3594.585 -170.787) 
(list 3520.5625 -170.137)))
(apply 'command (append '("pline") coords '("c")))
(setq currobj (ssadd (entlast) currobj))
(setq coords (list 
(list 3520.5625 -169.994) 
(list 3594.585 -170.644) 
(list 3594.585 -170.467) 
(list 3520.5625 -169.917)))
(apply 'command (append '("pline") coords '("c")))
(setq currobj (ssadd (entlast) currobj))
(setq coords (list 
(list 3520.5625 -169.774) 
(list 3594.585 -170.324) 
(list 3594.585 -170.147) 
(list 3520.5625 -169.697)))
(apply 'command (append '("pline") coords '("c")))
(setq currobj (ssadd (entlast) currobj))
(setq coords (list 
(list 3520.5625 -169.554) 
(list 3594.585 -170.004) 
(list 3594.585 -169.827) 
(list 3520.5625 -169.477)))
(apply 'command (append '("pline") coords '("c")))
(setq currobj (ssadd (entlast) currobj))
(setq coords (list 
(list 3520.5625 -169.334) 
(list 3594.585 -169.684) 
(list 3594.585 -169.507) 
(list 3520.5625 -169.257)))
(apply 'command (append '("pline") coords '("c")))
(setq currobj (ssadd (entlast) currobj))
(setq coords (list 
(list 3520.5625 -169.114) 
(list 3594.585 -169.364) 
(list 3594.585 -169.187) 
(list 3520.5625 -169.037)))
(apply 'command (append '("pline") coords '("c")))
(setq currobj (ssadd (entlast) currobj))
(setq coords (list 
(list 3520.5625 -168.894) 
(list 3594.585 -169.044) 
(list 3594.585 -168.867) 
(list 3520.5625 -168.817)))
(apply 'command (append '("pline") coords '("c")))
(setq currobj (ssadd (entlast) currobj))
(setq coords (list 
(list 3520.5625 -168.674) 
(list 3594.585 -168.724) 
(list 3594.585 -168.547) 
(list 3520.5625 -168.597)))
(apply 'command (append '("pline") coords '("c")))
(setq currobj (ssadd (entlast) currobj))
(setq coords (list 
(list 3520.5625 -168.454) 
(list 3594.585 -168.404) 
(list 3594.585 -168.227) 
(list 3520.5625 -168.377)))
(apply 'command (append '("pline") coords '("c")))
(setq currobj (ssadd (entlast) currobj))
(setq coords (list 
(list 3520.5625 -168.234) 
(list 3594.585 -168.084) 
(list 3594.585 -167.907) 
(list 3520.5625 -168.157)))
(apply 'command (append '("pline") coords '("c")))
(setq currobj (ssadd (entlast) currobj))
(setq coords (list 
(list 3520.5625 -168.014) 
(list 3594.585 -167.764) 
(list 3594.585 -167.587) 
(list 3520.5625 -167.937)))
(apply 'command (append '("pline") coords '("c")))
(setq currobj (ssadd (entlast) currobj))
(setq coords (list 
(list 3520.5625 -167.794) 
(list 3594.585 -167.444) 
(list 3594.585 -167.267) 
(list 3520.5625 -167.717)))
(apply 'command (append '("pline") coords '("c")))
(setq currobj (ssadd (entlast) currobj))
(setq coords (list 
(list 3520.5625 -167.574) 
(list 3594.585 -167.124) 
(list 3594.585 -166.947) 
(list 3520.5625 -167.497)))
(apply 'command (append '("pline") coords '("c")))
(setq currobj (ssadd (entlast) currobj))
(setq coords (list 
(list 3520.5625 -167.354) 
(list 3594.585 -166.804) 
(list 3594.585 -166.627) 
(list 3520.5625 -167.277)))
(apply 'command (append '("pline") coords '("c")))
(setq currobj (ssadd (entlast) currobj))
(setq coords (list 
(list 3520.5625 -167.134) 
(list 3594.585 -166.484) 
(list 3594.585 -166.307) 
(list 3520.5625 -167.057)))
(apply 'command (append '("pline") coords '("c")))
(setq currobj (ssadd (entlast) currobj))
(setq coords (list 
(list 3519.4375 -167.057) 
(list 3445.415 -166.307) 
(list 3445.415 -166.484) 
(list 3519.4375 -167.134)))
(apply 'command (append '("pline") coords '("c")))
(setq currobj (ssadd (entlast) currobj))
(setq coords (list 
(list 3519.4375 -167.277) 
(list 3445.415 -166.627) 
(list 3445.415 -166.804) 
(list 3519.4375 -167.354)))
(apply 'command (append '("pline") coords '("c")))
(setq currobj (ssadd (entlast) currobj))
(setq coords (list 
(list 3519.4375 -167.497) 
(list 3445.415 -166.947) 
(list 3445.415 -167.124) 
(list 3519.4375 -167.574)))
(apply 'command (append '("pline") coords '("c")))
(setq currobj (ssadd (entlast) currobj))
(setq coords (list 
(list 3519.4375 -167.717) 
(list 3445.415 -167.267) 
(list 3445.415 -167.444) 
(list 3519.4375 -167.794)))
(apply 'command (append '("pline") coords '("c")))
(setq currobj (ssadd (entlast) currobj))
(setq coords (list 
(list 3519.4375 -167.937) 
(list 3445.415 -167.587) 
(list 3445.415 -167.764) 
(list 3519.4375 -168.014)))
(apply 'command (append '("pline") coords '("c")))
(setq currobj (ssadd (entlast) currobj))
(setq coords (list 
(list 3519.4375 -168.157) 
(list 3445.415 -167.907) 
(list 3445.415 -168.084) 
(list 3519.4375 -168.234)))
(apply 'command (append '("pline") coords '("c")))
(setq currobj (ssadd (entlast) currobj))
(setq coords (list 
(list 3519.4375 -168.377) 
(list 3445.415 -168.227) 
(list 3445.415 -168.404) 
(list 3519.4375 -168.454)))
(apply 'command (append '("pline") coords '("c")))
(setq currobj (ssadd (entlast) currobj))
(setq coords (list 
(list 3519.4375 -168.597) 
(list 3445.415 -168.547) 
(list 3445.415 -168.724) 
(list 3519.4375 -168.674)))
(apply 'command (append '("pline") coords '("c")))
(setq currobj (ssadd (entlast) currobj))
(setq coords (list 
(list 3519.4375 -168.817) 
(list 3445.415 -168.867) 
(list 3445.415 -169.044) 
(list 3519.4375 -168.894)))
(apply 'command (append '("pline") coords '("c")))
(setq currobj (ssadd (entlast) currobj))
(setq coords (list 
(list 3519.4375 -169.037) 
(list 3445.415 -169.187) 
(list 3445.415 -169.364) 
(list 3519.4375 -169.114)))
(apply 'command (append '("pline") coords '("c")))
(setq currobj (ssadd (entlast) currobj))
(setq coords (list 
(list 3519.4375 -169.257) 
(list 3445.415 -169.507) 
(list 3445.415 -169.684) 
(list 3519.4375 -169.334)))
(apply 'command (append '("pline") coords '("c")))
(setq currobj (ssadd (entlast) currobj))
(setq coords (list 
(list 3519.4375 -169.477) 
(list 3445.415 -169.827) 
(list 3445.415 -170.004) 
(list 3519.4375 -169.554)))
(apply 'command (append '("pline") coords '("c")))
(setq currobj (ssadd (entlast) currobj))
(setq coords (list 
(list 3519.4375 -169.697) 
(list 3445.415 -170.147) 
(list 3445.415 -170.324) 
(list 3519.4375 -169.774)))
(apply 'command (append '("pline") coords '("c")))
(setq currobj (ssadd (entlast) currobj))
(setq coords (list 
(list 3519.4375 -169.917) 
(list 3445.415 -170.467) 
(list 3445.415 -170.644) 
(list 3519.4375 -169.994)))
(apply 'command (append '("pline") coords '("c")))
(setq currobj (ssadd (entlast) currobj))
(setq coords (list 
(list 3519.4375 -170.137) 
(list 3445.415 -170.787) 
(list 3445.415 -170.964) 
(list 3519.4375 -170.214)))
(apply 'command (append '("pline") coords '("c")))
(setq currobj (ssadd (entlast) currobj))
(command "_layer" "set" "nitride" "")
(command "_layer" "set" "text" "")
(command "_circle" "3519.0625,-181.357" "0.075")
(command "_circle" "3519.0625,-181.057" "0.075")
(command "_circle" "3519.0625,-180.757" "0.075")
(command "_circle" "3519.0625,-180.457" "0.075")
(command "_circle" "3519.0625,-180.157" "0.075")
(command "_circle" "3518.7625,-181.357" "0.075")
(command "_circle" "3518.7625,-181.057" "0.075")
(command "_circle" "3518.7625,-180.757" "0.075")
(command "_circle" "3518.7625,-180.457" "0.075")
(command "_circle" "3518.7625,-180.157" "0.075")
(command "_circle" "3518.4625,-181.357" "0.075")
(command "_circle" "3518.4625,-181.057" "0.075")
(command "_circle" "3518.4625,-180.757" "0.075")
(command "_circle" "3518.4625,-180.457" "0.075")
(command "_circle" "3518.4625,-180.157" "0.075")
(command "_circle" "3518.1625,-181.357" "0.075")
(command "_circle" "3518.1625,-181.057" "0.075")
(command "_circle" "3518.1625,-180.757" "0.075")
(command "_circle" "3518.1625,-180.457" "0.075")
(command "_circle" "3518.1625,-180.157" "0.075")
(command "_circle" "3517.8625,-181.357" "0.075")
(command "_circle" "3517.8625,-181.057" "0.075")
(command "_circle" "3517.8625,-180.757" "0.075")
(command "_circle" "3517.8625,-180.457" "0.075")
(command "_circle" "3517.8625,-180.157" "0.075")
(command "_layer" "set" "nitride" "")
(setq coords (list 
(list 3520.2625 -155.914) 
(list 3520.2625 -40.2693) 
(list 3519.7375 -40.2693) 
(list 3519.7375 -155.914)))
(apply 'command (append '("pline") coords '("c")))
(setq currobj (ssadd (entlast) currobj))
(command "_layer" "set" "prebias" "")
(command "_rectangle" "3519.7375,-155.914" "3520.2625,-40.2693")
(setq currobj (ssadd (entlast) currobj))
(command "_layer" "set" "nitride" "")
(setq coords (list 
(list 3520.2625 -40.2693) 
(list 3520.5625 -30.2693) 
(list 3520.5625 -30.2693) 
(list 3520.5625 -29.2693) 
(list 3594.585 -30.0193) 
(list 3594.585 -25.0763) 
(list 3520.5625 -25.8263) 
(list 3520.5625 -24.8263) 
(list 3520.5625 -24.8263) 
(list 3520.2625 -14.8263) 
(list 3519.7375 -14.8263) 
(list 3519.4375 -24.8263) 
(list 3519.4375 -24.8263) 
(list 3519.4375 -25.8263) 
(list 3445.415 -25.0763) 
(list 3445.415 -30.0193) 
(list 3519.4375 -29.2693) 
(list 3519.4375 -30.2693) 
(list 3519.4375 -30.2693) 
(list 3519.7375 -40.2693)))
(apply 'command (append '("pline") coords '("c")))
(setq currobj (ssadd (entlast) currobj))
(command "_layer" "set" "prebias" "")
(setq coords (list 
(list 3519.4375 -40.2693) 
(list 3519.4375 -29.2693) 
(list 3445.415 -30.0193) 
(list 3445.415 -25.0763) 
(list 3519.4375 -25.8263) 
(list 3519.4375 -14.8263) 
(list 3520.5625 -14.8263) 
(list 3520.5625 -25.8263) 
(list 3594.585 -25.0763) 
(list 3594.585 -30.0193) 
(list 3520.5625 -29.2693) 
(list 3520.5625 -40.2693)))
(apply 'command (append '("pline") coords '("c")))
(setq currobj (ssadd (entlast) currobj))
(command "_layer" "set" "nitride" "")
(command "_layer" "set" "fda1" "")
(setq coords (list 
(list 3520.5625 -29.1263) 
(list 3594.585 -29.8763) 
(list 3594.585 -29.6993) 
(list 3520.5625 -29.0493)))
(apply 'command (append '("pline") coords '("c")))
(setq currobj (ssadd (entlast) currobj))
(setq coords (list 
(list 3520.5625 -28.9063) 
(list 3594.585 -29.5563) 
(list 3594.585 -29.3793) 
(list 3520.5625 -28.8293)))
(apply 'command (append '("pline") coords '("c")))
(setq currobj (ssadd (entlast) currobj))
(setq coords (list 
(list 3520.5625 -28.6863) 
(list 3594.585 -29.2363) 
(list 3594.585 -29.0593) 
(list 3520.5625 -28.6093)))
(apply 'command (append '("pline") coords '("c")))
(setq currobj (ssadd (entlast) currobj))
(setq coords (list 
(list 3520.5625 -28.4663) 
(list 3594.585 -28.9163) 
(list 3594.585 -28.7393) 
(list 3520.5625 -28.3893)))
(apply 'command (append '("pline") coords '("c")))
(setq currobj (ssadd (entlast) currobj))
(setq coords (list 
(list 3520.5625 -28.2463) 
(list 3594.585 -28.5963) 
(list 3594.585 -28.4193) 
(list 3520.5625 -28.1693)))
(apply 'command (append '("pline") coords '("c")))
(setq currobj (ssadd (entlast) currobj))
(setq coords (list 
(list 3520.5625 -28.0263) 
(list 3594.585 -28.2763) 
(list 3594.585 -28.0993) 
(list 3520.5625 -27.9493)))
(apply 'command (append '("pline") coords '("c")))
(setq currobj (ssadd (entlast) currobj))
(setq coords (list 
(list 3520.5625 -27.8063) 
(list 3594.585 -27.9563) 
(list 3594.585 -27.7793) 
(list 3520.5625 -27.7293)))
(apply 'command (append '("pline") coords '("c")))
(setq currobj (ssadd (entlast) currobj))
(setq coords (list 
(list 3520.5625 -27.5863) 
(list 3594.585 -27.6363) 
(list 3594.585 -27.4593) 
(list 3520.5625 -27.5093)))
(apply 'command (append '("pline") coords '("c")))
(setq currobj (ssadd (entlast) currobj))
(setq coords (list 
(list 3520.5625 -27.3663) 
(list 3594.585 -27.3163) 
(list 3594.585 -27.1393) 
(list 3520.5625 -27.2893)))
(apply 'command (append '("pline") coords '("c")))
(setq currobj (ssadd (entlast) currobj))
(setq coords (list 
(list 3520.5625 -27.1463) 
(list 3594.585 -26.9963) 
(list 3594.585 -26.8193) 
(list 3520.5625 -27.0693)))
(apply 'command (append '("pline") coords '("c")))
(setq currobj (ssadd (entlast) currobj))
(setq coords (list 
(list 3520.5625 -26.9263) 
(list 3594.585 -26.6763) 
(list 3594.585 -26.4993) 
(list 3520.5625 -26.8493)))
(apply 'command (append '("pline") coords '("c")))
(setq currobj (ssadd (entlast) currobj))
(setq coords (list 
(list 3520.5625 -26.7063) 
(list 3594.585 -26.3563) 
(list 3594.585 -26.1793) 
(list 3520.5625 -26.6293)))
(apply 'command (append '("pline") coords '("c")))
(setq currobj (ssadd (entlast) currobj))
(setq coords (list 
(list 3520.5625 -26.4863) 
(list 3594.585 -26.0363) 
(list 3594.585 -25.8593) 
(list 3520.5625 -26.4093)))
(apply 'command (append '("pline") coords '("c")))
(setq currobj (ssadd (entlast) currobj))
(setq coords (list 
(list 3520.5625 -26.2663) 
(list 3594.585 -25.7163) 
(list 3594.585 -25.5393) 
(list 3520.5625 -26.1893)))
(apply 'command (append '("pline") coords '("c")))
(setq currobj (ssadd (entlast) currobj))
(setq coords (list 
(list 3520.5625 -26.0463) 
(list 3594.585 -25.3963) 
(list 3594.585 -25.2193) 
(list 3520.5625 -25.9693)))
(apply 'command (append '("pline") coords '("c")))
(setq currobj (ssadd (entlast) currobj))
(setq coords (list 
(list 3519.4375 -25.9693) 
(list 3445.415 -25.2193) 
(list 3445.415 -25.3963) 
(list 3519.4375 -26.0463)))
(apply 'command (append '("pline") coords '("c")))
(setq currobj (ssadd (entlast) currobj))
(setq coords (list 
(list 3519.4375 -26.1893) 
(list 3445.415 -25.5393) 
(list 3445.415 -25.7163) 
(list 3519.4375 -26.2663)))
(apply 'command (append '("pline") coords '("c")))
(setq currobj (ssadd (entlast) currobj))
(setq coords (list 
(list 3519.4375 -26.4093) 
(list 3445.415 -25.8593) 
(list 3445.415 -26.0363) 
(list 3519.4375 -26.4863)))
(apply 'command (append '("pline") coords '("c")))
(setq currobj (ssadd (entlast) currobj))
(setq coords (list 
(list 3519.4375 -26.6293) 
(list 3445.415 -26.1793) 
(list 3445.415 -26.3563) 
(list 3519.4375 -26.7063)))
(apply 'command (append '("pline") coords '("c")))
(setq currobj (ssadd (entlast) currobj))
(setq coords (list 
(list 3519.4375 -26.8493) 
(list 3445.415 -26.4993) 
(list 3445.415 -26.6763) 
(list 3519.4375 -26.9263)))
(apply 'command (append '("pline") coords '("c")))
(setq currobj (ssadd (entlast) currobj))
(setq coords (list 
(list 3519.4375 -27.0693) 
(list 3445.415 -26.8193) 
(list 3445.415 -26.9963) 
(list 3519.4375 -27.1463)))
(apply 'command (append '("pline") coords '("c")))
(setq currobj (ssadd (entlast) currobj))
(setq coords (list 
(list 3519.4375 -27.2893) 
(list 3445.415 -27.1393) 
(list 3445.415 -27.3163) 
(list 3519.4375 -27.3663)))
(apply 'command (append '("pline") coords '("c")))
(setq currobj (ssadd (entlast) currobj))
(setq coords (list 
(list 3519.4375 -27.5093) 
(list 3445.415 -27.4593) 
(list 3445.415 -27.6363) 
(list 3519.4375 -27.5863)))
(apply 'command (append '("pline") coords '("c")))
(setq currobj (ssadd (entlast) currobj))
(setq coords (list 
(list 3519.4375 -27.7293) 
(list 3445.415 -27.7793) 
(list 3445.415 -27.9563) 
(list 3519.4375 -27.8063)))
(apply 'command (append '("pline") coords '("c")))
(setq currobj (ssadd (entlast) currobj))
(setq coords (list 
(list 3519.4375 -27.9493) 
(list 3445.415 -28.0993) 
(list 3445.415 -28.2763) 
(list 3519.4375 -28.0263)))
(apply 'command (append '("pline") coords '("c")))
(setq currobj (ssadd (entlast) currobj))
(setq coords (list 
(list 3519.4375 -28.1693) 
(list 3445.415 -28.4193) 
(list 3445.415 -28.5963) 
(list 3519.4375 -28.2463)))
(apply 'command (append '("pline") coords '("c")))
(setq currobj (ssadd (entlast) currobj))
(setq coords (list 
(list 3519.4375 -28.3893) 
(list 3445.415 -28.7393) 
(list 3445.415 -28.9163) 
(list 3519.4375 -28.4663)))
(apply 'command (append '("pline") coords '("c")))
(setq currobj (ssadd (entlast) currobj))
(setq coords (list 
(list 3519.4375 -28.6093) 
(list 3445.415 -29.0593) 
(list 3445.415 -29.2363) 
(list 3519.4375 -28.6863)))
(apply 'command (append '("pline") coords '("c")))
(setq currobj (ssadd (entlast) currobj))
(setq coords (list 
(list 3519.4375 -28.8293) 
(list 3445.415 -29.3793) 
(list 3445.415 -29.5563) 
(list 3519.4375 -28.9063)))
(apply 'command (append '("pline") coords '("c")))
(setq currobj (ssadd (entlast) currobj))
(setq coords (list 
(list 3519.4375 -29.0493) 
(list 3445.415 -29.6993) 
(list 3445.415 -29.8763) 
(list 3519.4375 -29.1263)))
(apply 'command (append '("pline") coords '("c")))
(setq currobj (ssadd (entlast) currobj))
(command "_layer" "set" "nitride" "")
(command "_layer" "set" "text" "")
(command "_circle" "3519.0625,-40.2693" "0.075")
(command "_circle" "3519.0625,-39.9693" "0.075")
(command "_circle" "3519.0625,-39.6693" "0.075")
(command "_circle" "3519.0625,-39.3693" "0.075")
(command "_circle" "3519.0625,-39.0693" "0.075")
(command "_circle" "3518.7625,-40.2693" "0.075")
(command "_circle" "3518.7625,-39.9693" "0.075")
(command "_circle" "3518.7625,-39.6693" "0.075")
(command "_circle" "3518.7625,-39.3693" "0.075")
(command "_circle" "3518.7625,-39.0693" "0.075")
(command "_circle" "3518.4625,-40.2693" "0.075")
(command "_circle" "3518.4625,-39.9693" "0.075")
(command "_circle" "3518.4625,-39.6693" "0.075")
(command "_circle" "3518.4625,-39.3693" "0.075")
(command "_circle" "3518.4625,-39.0693" "0.075")
(command "_circle" "3518.1625,-40.2693" "0.075")
(command "_circle" "3518.1625,-39.9693" "0.075")
(command "_circle" "3518.1625,-39.6693" "0.075")
(command "_circle" "3518.1625,-39.3693" "0.075")
(command "_circle" "3518.1625,-39.0693" "0.075")
(command "_circle" "3517.8625,-40.2693" "0.075")
(command "_circle" "3517.8625,-39.9693" "0.075")
(command "_circle" "3517.8625,-39.6693" "0.075")
(command "_circle" "3517.8625,-39.3693" "0.075")
(command "_circle" "3517.8625,-39.0693" "0.075")
(command "_layer" "set" "nitride" "")
(setq coords (list 
(list 3520.2625 -14.8263) 
(list 3520.2625 100.8184) 
(list 3519.7375 100.8184) 
(list 3519.7375 -14.8263)))
(apply 'command (append '("pline") coords '("c")))
(setq currobj (ssadd (entlast) currobj))
(command "_layer" "set" "prebias" "")
(command "_rectangle" "3519.7375,-14.8263" "3520.2625,100.8184")
(setq currobj (ssadd (entlast) currobj))
(command "_layer" "set" "nitride" "")
(setq coords (list 
(list 3520.2625 100.8184) 
(list 3520.5625 110.8184) 
(list 3520.5625 110.8184) 
(list 3520.5625 111.8184) 
(list 3594.585 111.0684) 
(list 3594.585 116.0114) 
(list 3520.5625 115.2614) 
(list 3520.5625 116.2614) 
(list 3520.5625 116.2614) 
(list 3520.2625 126.2614) 
(list 3519.7375 126.2614) 
(list 3519.4375 116.2614) 
(list 3519.4375 116.2614) 
(list 3519.4375 115.2614) 
(list 3445.415 116.0114) 
(list 3445.415 111.0684) 
(list 3519.4375 111.8184) 
(list 3519.4375 110.8184) 
(list 3519.4375 110.8184) 
(list 3519.7375 100.8184)))
(apply 'command (append '("pline") coords '("c")))
(setq currobj (ssadd (entlast) currobj))
(command "_layer" "set" "prebias" "")
(setq coords (list 
(list 3519.4375 100.8184) 
(list 3519.4375 111.8184) 
(list 3445.415 111.0684) 
(list 3445.415 116.0114) 
(list 3519.4375 115.2614) 
(list 3519.4375 126.2614) 
(list 3520.5625 126.2614) 
(list 3520.5625 115.2614) 
(list 3594.585 116.0114) 
(list 3594.585 111.0684) 
(list 3520.5625 111.8184) 
(list 3520.5625 100.8184)))
(apply 'command (append '("pline") coords '("c")))
(setq currobj (ssadd (entlast) currobj))
(command "_layer" "set" "nitride" "")
(command "_layer" "set" "fda1" "")
(setq coords (list 
(list 3520.5625 111.9614) 
(list 3594.585 111.2114) 
(list 3594.585 111.3884) 
(list 3520.5625 112.0384)))
(apply 'command (append '("pline") coords '("c")))
(setq currobj (ssadd (entlast) currobj))
(setq coords (list 
(list 3520.5625 112.1814) 
(list 3594.585 111.5314) 
(list 3594.585 111.7084) 
(list 3520.5625 112.2584)))
(apply 'command (append '("pline") coords '("c")))
(setq currobj (ssadd (entlast) currobj))
(setq coords (list 
(list 3520.5625 112.4014) 
(list 3594.585 111.8514) 
(list 3594.585 112.0284) 
(list 3520.5625 112.4784)))
(apply 'command (append '("pline") coords '("c")))
(setq currobj (ssadd (entlast) currobj))
(setq coords (list 
(list 3520.5625 112.6214) 
(list 3594.585 112.1714) 
(list 3594.585 112.3484) 
(list 3520.5625 112.6984)))
(apply 'command (append '("pline") coords '("c")))
(setq currobj (ssadd (entlast) currobj))
(setq coords (list 
(list 3520.5625 112.8414) 
(list 3594.585 112.4914) 
(list 3594.585 112.6684) 
(list 3520.5625 112.9184)))
(apply 'command (append '("pline") coords '("c")))
(setq currobj (ssadd (entlast) currobj))
(setq coords (list 
(list 3520.5625 113.0614) 
(list 3594.585 112.8114) 
(list 3594.585 112.9884) 
(list 3520.5625 113.1384)))
(apply 'command (append '("pline") coords '("c")))
(setq currobj (ssadd (entlast) currobj))
(setq coords (list 
(list 3520.5625 113.2814) 
(list 3594.585 113.1314) 
(list 3594.585 113.3084) 
(list 3520.5625 113.3584)))
(apply 'command (append '("pline") coords '("c")))
(setq currobj (ssadd (entlast) currobj))
(setq coords (list 
(list 3520.5625 113.5014) 
(list 3594.585 113.4514) 
(list 3594.585 113.6284) 
(list 3520.5625 113.5784)))
(apply 'command (append '("pline") coords '("c")))
(setq currobj (ssadd (entlast) currobj))
(setq coords (list 
(list 3520.5625 113.7214) 
(list 3594.585 113.7714) 
(list 3594.585 113.9484) 
(list 3520.5625 113.7984)))
(apply 'command (append '("pline") coords '("c")))
(setq currobj (ssadd (entlast) currobj))
(setq coords (list 
(list 3520.5625 113.9414) 
(list 3594.585 114.0914) 
(list 3594.585 114.2684) 
(list 3520.5625 114.0184)))
(apply 'command (append '("pline") coords '("c")))
(setq currobj (ssadd (entlast) currobj))
(setq coords (list 
(list 3520.5625 114.1614) 
(list 3594.585 114.4114) 
(list 3594.585 114.5884) 
(list 3520.5625 114.2384)))
(apply 'command (append '("pline") coords '("c")))
(setq currobj (ssadd (entlast) currobj))
(setq coords (list 
(list 3520.5625 114.3814) 
(list 3594.585 114.7314) 
(list 3594.585 114.9084) 
(list 3520.5625 114.4584)))
(apply 'command (append '("pline") coords '("c")))
(setq currobj (ssadd (entlast) currobj))
(setq coords (list 
(list 3520.5625 114.6014) 
(list 3594.585 115.0514) 
(list 3594.585 115.2284) 
(list 3520.5625 114.6784)))
(apply 'command (append '("pline") coords '("c")))
(setq currobj (ssadd (entlast) currobj))
(setq coords (list 
(list 3520.5625 114.8214) 
(list 3594.585 115.3714) 
(list 3594.585 115.5484) 
(list 3520.5625 114.8984)))
(apply 'command (append '("pline") coords '("c")))
(setq currobj (ssadd (entlast) currobj))
(setq coords (list 
(list 3520.5625 115.0414) 
(list 3594.585 115.6914) 
(list 3594.585 115.8684) 
(list 3520.5625 115.1184)))
(apply 'command (append '("pline") coords '("c")))
(setq currobj (ssadd (entlast) currobj))
(setq coords (list 
(list 3519.4375 115.1184) 
(list 3445.415 115.8684) 
(list 3445.415 115.6914) 
(list 3519.4375 115.0414)))
(apply 'command (append '("pline") coords '("c")))
(setq currobj (ssadd (entlast) currobj))
(setq coords (list 
(list 3519.4375 114.8984) 
(list 3445.415 115.5484) 
(list 3445.415 115.3714) 
(list 3519.4375 114.8214)))
(apply 'command (append '("pline") coords '("c")))
(setq currobj (ssadd (entlast) currobj))
(setq coords (list 
(list 3519.4375 114.6784) 
(list 3445.415 115.2284) 
(list 3445.415 115.0514) 
(list 3519.4375 114.6014)))
(apply 'command (append '("pline") coords '("c")))
(setq currobj (ssadd (entlast) currobj))
(setq coords (list 
(list 3519.4375 114.4584) 
(list 3445.415 114.9084) 
(list 3445.415 114.7314) 
(list 3519.4375 114.3814)))
(apply 'command (append '("pline") coords '("c")))
(setq currobj (ssadd (entlast) currobj))
(setq coords (list 
(list 3519.4375 114.2384) 
(list 3445.415 114.5884) 
(list 3445.415 114.4114) 
(list 3519.4375 114.1614)))
(apply 'command (append '("pline") coords '("c")))
(setq currobj (ssadd (entlast) currobj))
(setq coords (list 
(list 3519.4375 114.0184) 
(list 3445.415 114.2684) 
(list 3445.415 114.0914) 
(list 3519.4375 113.9414)))
(apply 'command (append '("pline") coords '("c")))
(setq currobj (ssadd (entlast) currobj))
(setq coords (list 
(list 3519.4375 113.7984) 
(list 3445.415 113.9484) 
(list 3445.415 113.7714) 
(list 3519.4375 113.7214)))
(apply 'command (append '("pline") coords '("c")))
(setq currobj (ssadd (entlast) currobj))
(setq coords (list 
(list 3519.4375 113.5784) 
(list 3445.415 113.6284) 
(list 3445.415 113.4514) 
(list 3519.4375 113.5014)))
(apply 'command (append '("pline") coords '("c")))
(setq currobj (ssadd (entlast) currobj))
(setq coords (list 
(list 3519.4375 113.3584) 
(list 3445.415 113.3084) 
(list 3445.415 113.1314) 
(list 3519.4375 113.2814)))
(apply 'command (append '("pline") coords '("c")))
(setq currobj (ssadd (entlast) currobj))
(setq coords (list 
(list 3519.4375 113.1384) 
(list 3445.415 112.9884) 
(list 3445.415 112.8114) 
(list 3519.4375 113.0614)))
(apply 'command (append '("pline") coords '("c")))
(setq currobj (ssadd (entlast) currobj))
(setq coords (list 
(list 3519.4375 112.9184) 
(list 3445.415 112.6684) 
(list 3445.415 112.4914) 
(list 3519.4375 112.8414)))
(apply 'command (append '("pline") coords '("c")))
(setq currobj (ssadd (entlast) currobj))
(setq coords (list 
(list 3519.4375 112.6984) 
(list 3445.415 112.3484) 
(list 3445.415 112.1714) 
(list 3519.4375 112.6214)))
(apply 'command (append '("pline") coords '("c")))
(setq currobj (ssadd (entlast) currobj))
(setq coords (list 
(list 3519.4375 112.4784) 
(list 3445.415 112.0284) 
(list 3445.415 111.8514) 
(list 3519.4375 112.4014)))
(apply 'command (append '("pline") coords '("c")))
(setq currobj (ssadd (entlast) currobj))
(setq coords (list 
(list 3519.4375 112.2584) 
(list 3445.415 111.7084) 
(list 3445.415 111.5314) 
(list 3519.4375 112.1814)))
(apply 'command (append '("pline") coords '("c")))
(setq currobj (ssadd (entlast) currobj))
(setq coords (list 
(list 3519.4375 112.0384) 
(list 3445.415 111.3884) 
(list 3445.415 111.2114) 
(list 3519.4375 111.9614)))
(apply 'command (append '("pline") coords '("c")))
(setq currobj (ssadd (entlast) currobj))
(command "_layer" "set" "nitride" "")
(command "_layer" "set" "text" "")
(command "_circle" "3519.0625,100.8184" "0.075")
(command "_circle" "3519.0625,101.1184" "0.075")
(command "_circle" "3519.0625,101.4184" "0.075")
(command "_circle" "3519.0625,101.7184" "0.075")
(command "_circle" "3519.0625,102.0184" "0.075")
(command "_circle" "3518.7625,100.8184" "0.075")
(command "_circle" "3518.7625,101.1184" "0.075")
(command "_circle" "3518.7625,101.4184" "0.075")
(command "_circle" "3518.7625,101.7184" "0.075")
(command "_circle" "3518.7625,102.0184" "0.075")
(command "_circle" "3518.4625,100.8184" "0.075")
(command "_circle" "3518.4625,101.1184" "0.075")
(command "_circle" "3518.4625,101.4184" "0.075")
(command "_circle" "3518.4625,101.7184" "0.075")
(command "_circle" "3518.4625,102.0184" "0.075")
(command "_circle" "3518.1625,100.8184" "0.075")
(command "_circle" "3518.1625,101.1184" "0.075")
(command "_circle" "3518.1625,101.4184" "0.075")
(command "_circle" "3518.1625,101.7184" "0.075")
(command "_circle" "3518.1625,102.0184" "0.075")
(command "_circle" "3517.8625,100.8184" "0.075")
(command "_circle" "3517.8625,101.1184" "0.075")
(command "_circle" "3517.8625,101.4184" "0.075")
(command "_circle" "3517.8625,101.7184" "0.075")
(command "_circle" "3517.8625,102.0184" "0.075")
(command "_layer" "set" "nitride" "")
(setq coords (list 
(list 3520.2625 126.2614) 
(list 3520.2625 241.9061) 
(list 3519.7375 241.9061) 
(list 3519.7375 126.2614)))
(apply 'command (append '("pline") coords '("c")))
(setq currobj (ssadd (entlast) currobj))
(command "_layer" "set" "prebias" "")
(command "_rectangle" "3519.7375,126.2614" "3520.2625,241.9061")
(setq currobj (ssadd (entlast) currobj))
(command "_layer" "set" "nitride" "")
(setq coords (list 
(list 3520.2625 241.9061) 
(list 3520.5625 251.9061) 
(list 3520.5625 251.9061) 
(list 3520.5625 252.9061) 
(list 3594.585 252.1561) 
(list 3594.585 257.0991) 
(list 3520.5625 256.3491) 
(list 3520.5625 257.3491) 
(list 3520.5625 257.3491) 
(list 3520.2625 267.3491) 
(list 3519.7375 267.3491) 
(list 3519.4375 257.3491) 
(list 3519.4375 257.3491) 
(list 3519.4375 256.3491) 
(list 3445.415 257.0991) 
(list 3445.415 252.1561) 
(list 3519.4375 252.9061) 
(list 3519.4375 251.9061) 
(list 3519.4375 251.9061) 
(list 3519.7375 241.9061)))
(apply 'command (append '("pline") coords '("c")))
(setq currobj (ssadd (entlast) currobj))
(command "_layer" "set" "prebias" "")
(setq coords (list 
(list 3519.4375 241.9061) 
(list 3519.4375 252.9061) 
(list 3445.415 252.1561) 
(list 3445.415 257.0991) 
(list 3519.4375 256.3491) 
(list 3519.4375 267.3491) 
(list 3520.5625 267.3491) 
(list 3520.5625 256.3491) 
(list 3594.585 257.0991) 
(list 3594.585 252.1561) 
(list 3520.5625 252.9061) 
(list 3520.5625 241.9061)))
(apply 'command (append '("pline") coords '("c")))
(setq currobj (ssadd (entlast) currobj))
(command "_layer" "set" "nitride" "")
(command "_layer" "set" "fda1" "")
(setq coords (list 
(list 3520.5625 253.0491) 
(list 3594.585 252.2991) 
(list 3594.585 252.4761) 
(list 3520.5625 253.1261)))
(apply 'command (append '("pline") coords '("c")))
(setq currobj (ssadd (entlast) currobj))
(setq coords (list 
(list 3520.5625 253.2691) 
(list 3594.585 252.6191) 
(list 3594.585 252.7961) 
(list 3520.5625 253.3461)))
(apply 'command (append '("pline") coords '("c")))
(setq currobj (ssadd (entlast) currobj))
(setq coords (list 
(list 3520.5625 253.4891) 
(list 3594.585 252.9391) 
(list 3594.585 253.1161) 
(list 3520.5625 253.5661)))
(apply 'command (append '("pline") coords '("c")))
(setq currobj (ssadd (entlast) currobj))
(setq coords (list 
(list 3520.5625 253.7091) 
(list 3594.585 253.2591) 
(list 3594.585 253.4361) 
(list 3520.5625 253.7861)))
(apply 'command (append '("pline") coords '("c")))
(setq currobj (ssadd (entlast) currobj))
(setq coords (list 
(list 3520.5625 253.9291) 
(list 3594.585 253.5791) 
(list 3594.585 253.7561) 
(list 3520.5625 254.0061)))
(apply 'command (append '("pline") coords '("c")))
(setq currobj (ssadd (entlast) currobj))
(setq coords (list 
(list 3520.5625 254.1491) 
(list 3594.585 253.8991) 
(list 3594.585 254.0761) 
(list 3520.5625 254.2261)))
(apply 'command (append '("pline") coords '("c")))
(setq currobj (ssadd (entlast) currobj))
(setq coords (list 
(list 3520.5625 254.3691) 
(list 3594.585 254.2191) 
(list 3594.585 254.3961) 
(list 3520.5625 254.4461)))
(apply 'command (append '("pline") coords '("c")))
(setq currobj (ssadd (entlast) currobj))
(setq coords (list 
(list 3520.5625 254.5891) 
(list 3594.585 254.5391) 
(list 3594.585 254.7161) 
(list 3520.5625 254.6661)))
(apply 'command (append '("pline") coords '("c")))
(setq currobj (ssadd (entlast) currobj))
(setq coords (list 
(list 3520.5625 254.8091) 
(list 3594.585 254.8591) 
(list 3594.585 255.0361) 
(list 3520.5625 254.8861)))
(apply 'command (append '("pline") coords '("c")))
(setq currobj (ssadd (entlast) currobj))
(setq coords (list 
(list 3520.5625 255.0291) 
(list 3594.585 255.1791) 
(list 3594.585 255.3561) 
(list 3520.5625 255.1061)))
(apply 'command (append '("pline") coords '("c")))
(setq currobj (ssadd (entlast) currobj))
(setq coords (list 
(list 3520.5625 255.2491) 
(list 3594.585 255.4991) 
(list 3594.585 255.6761) 
(list 3520.5625 255.3261)))
(apply 'command (append '("pline") coords '("c")))
(setq currobj (ssadd (entlast) currobj))
(setq coords (list 
(list 3520.5625 255.4691) 
(list 3594.585 255.8191) 
(list 3594.585 255.9961) 
(list 3520.5625 255.5461)))
(apply 'command (append '("pline") coords '("c")))
(setq currobj (ssadd (entlast) currobj))
(setq coords (list 
(list 3520.5625 255.6891) 
(list 3594.585 256.1391) 
(list 3594.585 256.3161) 
(list 3520.5625 255.7661)))
(apply 'command (append '("pline") coords '("c")))
(setq currobj (ssadd (entlast) currobj))
(setq coords (list 
(list 3520.5625 255.9091) 
(list 3594.585 256.4591) 
(list 3594.585 256.6361) 
(list 3520.5625 255.9861)))
(apply 'command (append '("pline") coords '("c")))
(setq currobj (ssadd (entlast) currobj))
(setq coords (list 
(list 3520.5625 256.1291) 
(list 3594.585 256.7791) 
(list 3594.585 256.9561) 
(list 3520.5625 256.2061)))
(apply 'command (append '("pline") coords '("c")))
(setq currobj (ssadd (entlast) currobj))
(setq coords (list 
(list 3519.4375 256.2061) 
(list 3445.415 256.9561) 
(list 3445.415 256.7791) 
(list 3519.4375 256.1291)))
(apply 'command (append '("pline") coords '("c")))
(setq currobj (ssadd (entlast) currobj))
(setq coords (list 
(list 3519.4375 255.9861) 
(list 3445.415 256.6361) 
(list 3445.415 256.4591) 
(list 3519.4375 255.9091)))
(apply 'command (append '("pline") coords '("c")))
(setq currobj (ssadd (entlast) currobj))
(setq coords (list 
(list 3519.4375 255.7661) 
(list 3445.415 256.3161) 
(list 3445.415 256.1391) 
(list 3519.4375 255.6891)))
(apply 'command (append '("pline") coords '("c")))
(setq currobj (ssadd (entlast) currobj))
(setq coords (list 
(list 3519.4375 255.5461) 
(list 3445.415 255.9961) 
(list 3445.415 255.8191) 
(list 3519.4375 255.4691)))
(apply 'command (append '("pline") coords '("c")))
(setq currobj (ssadd (entlast) currobj))
(setq coords (list 
(list 3519.4375 255.3261) 
(list 3445.415 255.6761) 
(list 3445.415 255.4991) 
(list 3519.4375 255.2491)))
(apply 'command (append '("pline") coords '("c")))
(setq currobj (ssadd (entlast) currobj))
(setq coords (list 
(list 3519.4375 255.1061) 
(list 3445.415 255.3561) 
(list 3445.415 255.1791) 
(list 3519.4375 255.0291)))
(apply 'command (append '("pline") coords '("c")))
(setq currobj (ssadd (entlast) currobj))
(setq coords (list 
(list 3519.4375 254.8861) 
(list 3445.415 255.0361) 
(list 3445.415 254.8591) 
(list 3519.4375 254.8091)))
(apply 'command (append '("pline") coords '("c")))
(setq currobj (ssadd (entlast) currobj))
(setq coords (list 
(list 3519.4375 254.6661) 
(list 3445.415 254.7161) 
(list 3445.415 254.5391) 
(list 3519.4375 254.5891)))
(apply 'command (append '("pline") coords '("c")))
(setq currobj (ssadd (entlast) currobj))
(setq coords (list 
(list 3519.4375 254.4461) 
(list 3445.415 254.3961) 
(list 3445.415 254.2191) 
(list 3519.4375 254.3691)))
(apply 'command (append '("pline") coords '("c")))
(setq currobj (ssadd (entlast) currobj))
(setq coords (list 
(list 3519.4375 254.2261) 
(list 3445.415 254.0761) 
(list 3445.415 253.8991) 
(list 3519.4375 254.1491)))
(apply 'command (append '("pline") coords '("c")))
(setq currobj (ssadd (entlast) currobj))
(setq coords (list 
(list 3519.4375 254.0061) 
(list 3445.415 253.7561) 
(list 3445.415 253.5791) 
(list 3519.4375 253.9291)))
(apply 'command (append '("pline") coords '("c")))
(setq currobj (ssadd (entlast) currobj))
(setq coords (list 
(list 3519.4375 253.7861) 
(list 3445.415 253.4361) 
(list 3445.415 253.2591) 
(list 3519.4375 253.7091)))
(apply 'command (append '("pline") coords '("c")))
(setq currobj (ssadd (entlast) currobj))
(setq coords (list 
(list 3519.4375 253.5661) 
(list 3445.415 253.1161) 
(list 3445.415 252.9391) 
(list 3519.4375 253.4891)))
(apply 'command (append '("pline") coords '("c")))
(setq currobj (ssadd (entlast) currobj))
(setq coords (list 
(list 3519.4375 253.3461) 
(list 3445.415 252.7961) 
(list 3445.415 252.6191) 
(list 3519.4375 253.2691)))
(apply 'command (append '("pline") coords '("c")))
(setq currobj (ssadd (entlast) currobj))
(setq coords (list 
(list 3519.4375 253.1261) 
(list 3445.415 252.4761) 
(list 3445.415 252.2991) 
(list 3519.4375 253.0491)))
(apply 'command (append '("pline") coords '("c")))
(setq currobj (ssadd (entlast) currobj))
(command "_layer" "set" "nitride" "")
(command "_layer" "set" "text" "")
(command "_circle" "3519.0625,241.9061" "0.075")
(command "_circle" "3519.0625,242.2061" "0.075")
(command "_circle" "3519.0625,242.5061" "0.075")
(command "_circle" "3519.0625,242.8061" "0.075")
(command "_circle" "3519.0625,243.1061" "0.075")
(command "_circle" "3518.7625,241.9061" "0.075")
(command "_circle" "3518.7625,242.2061" "0.075")
(command "_circle" "3518.7625,242.5061" "0.075")
(command "_circle" "3518.7625,242.8061" "0.075")
(command "_circle" "3518.7625,243.1061" "0.075")
(command "_circle" "3518.4625,241.9061" "0.075")
(command "_circle" "3518.4625,242.2061" "0.075")
(command "_circle" "3518.4625,242.5061" "0.075")
(command "_circle" "3518.4625,242.8061" "0.075")
(command "_circle" "3518.4625,243.1061" "0.075")
(command "_circle" "3518.1625,241.9061" "0.075")
(command "_circle" "3518.1625,242.2061" "0.075")
(command "_circle" "3518.1625,242.5061" "0.075")
(command "_circle" "3518.1625,242.8061" "0.075")
(command "_circle" "3518.1625,243.1061" "0.075")
(command "_circle" "3517.8625,241.9061" "0.075")
(command "_circle" "3517.8625,242.2061" "0.075")
(command "_circle" "3517.8625,242.5061" "0.075")
(command "_circle" "3517.8625,242.8061" "0.075")
(command "_circle" "3517.8625,243.1061" "0.075")
(command "_layer" "set" "nitride" "")
(setq coords (list 
(list 3520.2625 267.3491) 
(list 3520.2625 382.9939) 
(list 3519.7375 382.9939) 
(list 3519.7375 267.3491)))
(apply 'command (append '("pline") coords '("c")))
(setq currobj (ssadd (entlast) currobj))
(command "_layer" "set" "prebias" "")
(command "_rectangle" "3519.7375,267.3491" "3520.2625,382.9939")
(setq currobj (ssadd (entlast) currobj))
(command "_layer" "set" "nitride" "")
(setq coords (list 
(list 3520.2625 382.9939) 
(list 3520.5625 392.9939) 
(list 3520.5625 392.9939) 
(list 3520.5625 393.9939) 
(list 3594.585 393.2439) 
(list 3594.585 398.1869) 
(list 3520.5625 397.4369) 
(list 3520.5625 398.4369) 
(list 3520.5625 398.4369) 
(list 3520.2625 408.4369) 
(list 3519.7375 408.4369) 
(list 3519.4375 398.4369) 
(list 3519.4375 398.4369) 
(list 3519.4375 397.4369) 
(list 3445.415 398.1869) 
(list 3445.415 393.2439) 
(list 3519.4375 393.9939) 
(list 3519.4375 392.9939) 
(list 3519.4375 392.9939) 
(list 3519.7375 382.9939)))
(apply 'command (append '("pline") coords '("c")))
(setq currobj (ssadd (entlast) currobj))
(command "_layer" "set" "prebias" "")
(setq coords (list 
(list 3519.4375 382.9939) 
(list 3519.4375 393.9939) 
(list 3445.415 393.2439) 
(list 3445.415 398.1869) 
(list 3519.4375 397.4369) 
(list 3519.4375 408.4369) 
(list 3520.5625 408.4369) 
(list 3520.5625 397.4369) 
(list 3594.585 398.1869) 
(list 3594.585 393.2439) 
(list 3520.5625 393.9939) 
(list 3520.5625 382.9939)))
(apply 'command (append '("pline") coords '("c")))
(setq currobj (ssadd (entlast) currobj))
(command "_layer" "set" "nitride" "")
(command "_layer" "set" "fda1" "")
(setq coords (list 
(list 3520.5625 394.1369) 
(list 3594.585 393.3869) 
(list 3594.585 393.5639) 
(list 3520.5625 394.2139)))
(apply 'command (append '("pline") coords '("c")))
(setq currobj (ssadd (entlast) currobj))
(setq coords (list 
(list 3520.5625 394.3569) 
(list 3594.585 393.7069) 
(list 3594.585 393.8839) 
(list 3520.5625 394.4339)))
(apply 'command (append '("pline") coords '("c")))
(setq currobj (ssadd (entlast) currobj))
(setq coords (list 
(list 3520.5625 394.5769) 
(list 3594.585 394.0269) 
(list 3594.585 394.2039) 
(list 3520.5625 394.6539)))
(apply 'command (append '("pline") coords '("c")))
(setq currobj (ssadd (entlast) currobj))
(setq coords (list 
(list 3520.5625 394.7969) 
(list 3594.585 394.3469) 
(list 3594.585 394.5239) 
(list 3520.5625 394.8739)))
(apply 'command (append '("pline") coords '("c")))
(setq currobj (ssadd (entlast) currobj))
(setq coords (list 
(list 3520.5625 395.0169) 
(list 3594.585 394.6669) 
(list 3594.585 394.8439) 
(list 3520.5625 395.0939)))
(apply 'command (append '("pline") coords '("c")))
(setq currobj (ssadd (entlast) currobj))
(setq coords (list 
(list 3520.5625 395.2369) 
(list 3594.585 394.9869) 
(list 3594.585 395.1639) 
(list 3520.5625 395.3139)))
(apply 'command (append '("pline") coords '("c")))
(setq currobj (ssadd (entlast) currobj))
(setq coords (list 
(list 3520.5625 395.4569) 
(list 3594.585 395.3069) 
(list 3594.585 395.4839) 
(list 3520.5625 395.5339)))
(apply 'command (append '("pline") coords '("c")))
(setq currobj (ssadd (entlast) currobj))
(setq coords (list 
(list 3520.5625 395.6769) 
(list 3594.585 395.6269) 
(list 3594.585 395.8039) 
(list 3520.5625 395.7539)))
(apply 'command (append '("pline") coords '("c")))
(setq currobj (ssadd (entlast) currobj))
(setq coords (list 
(list 3520.5625 395.8969) 
(list 3594.585 395.9469) 
(list 3594.585 396.1239) 
(list 3520.5625 395.9739)))
(apply 'command (append '("pline") coords '("c")))
(setq currobj (ssadd (entlast) currobj))
(setq coords (list 
(list 3520.5625 396.1169) 
(list 3594.585 396.2669) 
(list 3594.585 396.4439) 
(list 3520.5625 396.1939)))
(apply 'command (append '("pline") coords '("c")))
(setq currobj (ssadd (entlast) currobj))
(setq coords (list 
(list 3520.5625 396.3369) 
(list 3594.585 396.5869) 
(list 3594.585 396.7639) 
(list 3520.5625 396.4139)))
(apply 'command (append '("pline") coords '("c")))
(setq currobj (ssadd (entlast) currobj))
(setq coords (list 
(list 3520.5625 396.5569) 
(list 3594.585 396.9069) 
(list 3594.585 397.0839) 
(list 3520.5625 396.6339)))
(apply 'command (append '("pline") coords '("c")))
(setq currobj (ssadd (entlast) currobj))
(setq coords (list 
(list 3520.5625 396.7769) 
(list 3594.585 397.2269) 
(list 3594.585 397.4039) 
(list 3520.5625 396.8539)))
(apply 'command (append '("pline") coords '("c")))
(setq currobj (ssadd (entlast) currobj))
(setq coords (list 
(list 3520.5625 396.9969) 
(list 3594.585 397.5469) 
(list 3594.585 397.7239) 
(list 3520.5625 397.0739)))
(apply 'command (append '("pline") coords '("c")))
(setq currobj (ssadd (entlast) currobj))
(setq coords (list 
(list 3520.5625 397.2169) 
(list 3594.585 397.8669) 
(list 3594.585 398.0439) 
(list 3520.5625 397.2939)))
(apply 'command (append '("pline") coords '("c")))
(setq currobj (ssadd (entlast) currobj))
(setq coords (list 
(list 3519.4375 397.2939) 
(list 3445.415 398.0439) 
(list 3445.415 397.8669) 
(list 3519.4375 397.2169)))
(apply 'command (append '("pline") coords '("c")))
(setq currobj (ssadd (entlast) currobj))
(setq coords (list 
(list 3519.4375 397.0739) 
(list 3445.415 397.7239) 
(list 3445.415 397.5469) 
(list 3519.4375 396.9969)))
(apply 'command (append '("pline") coords '("c")))
(setq currobj (ssadd (entlast) currobj))
(setq coords (list 
(list 3519.4375 396.8539) 
(list 3445.415 397.4039) 
(list 3445.415 397.2269) 
(list 3519.4375 396.7769)))
(apply 'command (append '("pline") coords '("c")))
(setq currobj (ssadd (entlast) currobj))
(setq coords (list 
(list 3519.4375 396.6339) 
(list 3445.415 397.0839) 
(list 3445.415 396.9069) 
(list 3519.4375 396.5569)))
(apply 'command (append '("pline") coords '("c")))
(setq currobj (ssadd (entlast) currobj))
(setq coords (list 
(list 3519.4375 396.4139) 
(list 3445.415 396.7639) 
(list 3445.415 396.5869) 
(list 3519.4375 396.3369)))
(apply 'command (append '("pline") coords '("c")))
(setq currobj (ssadd (entlast) currobj))
(setq coords (list 
(list 3519.4375 396.1939) 
(list 3445.415 396.4439) 
(list 3445.415 396.2669) 
(list 3519.4375 396.1169)))
(apply 'command (append '("pline") coords '("c")))
(setq currobj (ssadd (entlast) currobj))
(setq coords (list 
(list 3519.4375 395.9739) 
(list 3445.415 396.1239) 
(list 3445.415 395.9469) 
(list 3519.4375 395.8969)))
(apply 'command (append '("pline") coords '("c")))
(setq currobj (ssadd (entlast) currobj))
(setq coords (list 
(list 3519.4375 395.7539) 
(list 3445.415 395.8039) 
(list 3445.415 395.6269) 
(list 3519.4375 395.6769)))
(apply 'command (append '("pline") coords '("c")))
(setq currobj (ssadd (entlast) currobj))
(setq coords (list 
(list 3519.4375 395.5339) 
(list 3445.415 395.4839) 
(list 3445.415 395.3069) 
(list 3519.4375 395.4569)))
(apply 'command (append '("pline") coords '("c")))
(setq currobj (ssadd (entlast) currobj))
(setq coords (list 
(list 3519.4375 395.3139) 
(list 3445.415 395.1639) 
(list 3445.415 394.9869) 
(list 3519.4375 395.2369)))
(apply 'command (append '("pline") coords '("c")))
(setq currobj (ssadd (entlast) currobj))
(setq coords (list 
(list 3519.4375 395.0939) 
(list 3445.415 394.8439) 
(list 3445.415 394.6669) 
(list 3519.4375 395.0169)))
(apply 'command (append '("pline") coords '("c")))
(setq currobj (ssadd (entlast) currobj))
(setq coords (list 
(list 3519.4375 394.8739) 
(list 3445.415 394.5239) 
(list 3445.415 394.3469) 
(list 3519.4375 394.7969)))
(apply 'command (append '("pline") coords '("c")))
(setq currobj (ssadd (entlast) currobj))
(setq coords (list 
(list 3519.4375 394.6539) 
(list 3445.415 394.2039) 
(list 3445.415 394.0269) 
(list 3519.4375 394.5769)))
(apply 'command (append '("pline") coords '("c")))
(setq currobj (ssadd (entlast) currobj))
(setq coords (list 
(list 3519.4375 394.4339) 
(list 3445.415 393.8839) 
(list 3445.415 393.7069) 
(list 3519.4375 394.3569)))
(apply 'command (append '("pline") coords '("c")))
(setq currobj (ssadd (entlast) currobj))
(setq coords (list 
(list 3519.4375 394.2139) 
(list 3445.415 393.5639) 
(list 3445.415 393.3869) 
(list 3519.4375 394.1369)))
(apply 'command (append '("pline") coords '("c")))
(setq currobj (ssadd (entlast) currobj))
(command "_layer" "set" "nitride" "")
(command "_layer" "set" "text" "")
(command "_circle" "3519.0625,382.9939" "0.075")
(command "_circle" "3519.0625,383.2939" "0.075")
(command "_circle" "3519.0625,383.5939" "0.075")
(command "_circle" "3519.0625,383.8939" "0.075")
(command "_circle" "3519.0625,384.1939" "0.075")
(command "_circle" "3518.7625,382.9939" "0.075")
(command "_circle" "3518.7625,383.2939" "0.075")
(command "_circle" "3518.7625,383.5939" "0.075")
(command "_circle" "3518.7625,383.8939" "0.075")
(command "_circle" "3518.7625,384.1939" "0.075")
(command "_circle" "3518.4625,382.9939" "0.075")
(command "_circle" "3518.4625,383.2939" "0.075")
(command "_circle" "3518.4625,383.5939" "0.075")
(command "_circle" "3518.4625,383.8939" "0.075")
(command "_circle" "3518.4625,384.1939" "0.075")
(command "_circle" "3518.1625,382.9939" "0.075")
(command "_circle" "3518.1625,383.2939" "0.075")
(command "_circle" "3518.1625,383.5939" "0.075")
(command "_circle" "3518.1625,383.8939" "0.075")
(command "_circle" "3518.1625,384.1939" "0.075")
(command "_circle" "3517.8625,382.9939" "0.075")
(command "_circle" "3517.8625,383.2939" "0.075")
(command "_circle" "3517.8625,383.5939" "0.075")
(command "_circle" "3517.8625,383.8939" "0.075")
(command "_circle" "3517.8625,384.1939" "0.075")
(command "_layer" "set" "nitride" "")
(setq coords (list 
(list 3520.2625 408.4369) 
(list 3520.2625 524.0816) 
(list 3519.7375 524.0816) 
(list 3519.7375 408.4369)))
(apply 'command (append '("pline") coords '("c")))
(setq currobj (ssadd (entlast) currobj))
(command "_layer" "set" "prebias" "")
(command "_rectangle" "3519.7375,408.4369" "3520.2625,524.0816")
(setq currobj (ssadd (entlast) currobj))
(command "_layer" "set" "nitride" "")
(setq coords (list 
(list 3520.2625 524.0816) 
(list 3520.5625 534.0816) 
(list 3520.5625 534.0816) 
(list 3520.5625 535.0816) 
(list 3594.585 534.3316) 
(list 3594.585 539.2746) 
(list 3520.5625 538.5246) 
(list 3520.5625 539.5246) 
(list 3520.5625 539.5246) 
(list 3520.2625 549.5246) 
(list 3519.7375 549.5246) 
(list 3519.4375 539.5246) 
(list 3519.4375 539.5246) 
(list 3519.4375 538.5246) 
(list 3445.415 539.2746) 
(list 3445.415 534.3316) 
(list 3519.4375 535.0816) 
(list 3519.4375 534.0816) 
(list 3519.4375 534.0816) 
(list 3519.7375 524.0816)))
(apply 'command (append '("pline") coords '("c")))
(setq currobj (ssadd (entlast) currobj))
(command "_layer" "set" "prebias" "")
(setq coords (list 
(list 3519.4375 524.0816) 
(list 3519.4375 535.0816) 
(list 3445.415 534.3316) 
(list 3445.415 539.2746) 
(list 3519.4375 538.5246) 
(list 3519.4375 549.5246) 
(list 3520.5625 549.5246) 
(list 3520.5625 538.5246) 
(list 3594.585 539.2746) 
(list 3594.585 534.3316) 
(list 3520.5625 535.0816) 
(list 3520.5625 524.0816)))
(apply 'command (append '("pline") coords '("c")))
(setq currobj (ssadd (entlast) currobj))
(command "_layer" "set" "nitride" "")
(command "_layer" "set" "fda1" "")
(setq coords (list 
(list 3520.5625 535.2246) 
(list 3594.585 534.4746) 
(list 3594.585 534.6516) 
(list 3520.5625 535.3016)))
(apply 'command (append '("pline") coords '("c")))
(setq currobj (ssadd (entlast) currobj))
(setq coords (list 
(list 3520.5625 535.4446) 
(list 3594.585 534.7946) 
(list 3594.585 534.9716) 
(list 3520.5625 535.5216)))
(apply 'command (append '("pline") coords '("c")))
(setq currobj (ssadd (entlast) currobj))
(setq coords (list 
(list 3520.5625 535.6646) 
(list 3594.585 535.1146) 
(list 3594.585 535.2916) 
(list 3520.5625 535.7416)))
(apply 'command (append '("pline") coords '("c")))
(setq currobj (ssadd (entlast) currobj))
(setq coords (list 
(list 3520.5625 535.8846) 
(list 3594.585 535.4346) 
(list 3594.585 535.6116) 
(list 3520.5625 535.9616)))
(apply 'command (append '("pline") coords '("c")))
(setq currobj (ssadd (entlast) currobj))
(setq coords (list 
(list 3520.5625 536.1046) 
(list 3594.585 535.7546) 
(list 3594.585 535.9316) 
(list 3520.5625 536.1816)))
(apply 'command (append '("pline") coords '("c")))
(setq currobj (ssadd (entlast) currobj))
(setq coords (list 
(list 3520.5625 536.3246) 
(list 3594.585 536.0746) 
(list 3594.585 536.2516) 
(list 3520.5625 536.4016)))
(apply 'command (append '("pline") coords '("c")))
(setq currobj (ssadd (entlast) currobj))
(setq coords (list 
(list 3520.5625 536.5446) 
(list 3594.585 536.3946) 
(list 3594.585 536.5716) 
(list 3520.5625 536.6216)))
(apply 'command (append '("pline") coords '("c")))
(setq currobj (ssadd (entlast) currobj))
(setq coords (list 
(list 3520.5625 536.7646) 
(list 3594.585 536.7146) 
(list 3594.585 536.8916) 
(list 3520.5625 536.8416)))
(apply 'command (append '("pline") coords '("c")))
(setq currobj (ssadd (entlast) currobj))
(setq coords (list 
(list 3520.5625 536.9846) 
(list 3594.585 537.0346) 
(list 3594.585 537.2116) 
(list 3520.5625 537.0616)))
(apply 'command (append '("pline") coords '("c")))
(setq currobj (ssadd (entlast) currobj))
(setq coords (list 
(list 3520.5625 537.2046) 
(list 3594.585 537.3546) 
(list 3594.585 537.5316) 
(list 3520.5625 537.2816)))
(apply 'command (append '("pline") coords '("c")))
(setq currobj (ssadd (entlast) currobj))
(setq coords (list 
(list 3520.5625 537.4246) 
(list 3594.585 537.6746) 
(list 3594.585 537.8516) 
(list 3520.5625 537.5016)))
(apply 'command (append '("pline") coords '("c")))
(setq currobj (ssadd (entlast) currobj))
(setq coords (list 
(list 3520.5625 537.6446) 
(list 3594.585 537.9946) 
(list 3594.585 538.1716) 
(list 3520.5625 537.7216)))
(apply 'command (append '("pline") coords '("c")))
(setq currobj (ssadd (entlast) currobj))
(setq coords (list 
(list 3520.5625 537.8646) 
(list 3594.585 538.3146) 
(list 3594.585 538.4916) 
(list 3520.5625 537.9416)))
(apply 'command (append '("pline") coords '("c")))
(setq currobj (ssadd (entlast) currobj))
(setq coords (list 
(list 3520.5625 538.0846) 
(list 3594.585 538.6346) 
(list 3594.585 538.8116) 
(list 3520.5625 538.1616)))
(apply 'command (append '("pline") coords '("c")))
(setq currobj (ssadd (entlast) currobj))
(setq coords (list 
(list 3520.5625 538.3046) 
(list 3594.585 538.9546) 
(list 3594.585 539.1316) 
(list 3520.5625 538.3816)))
(apply 'command (append '("pline") coords '("c")))
(setq currobj (ssadd (entlast) currobj))
(setq coords (list 
(list 3519.4375 538.3816) 
(list 3445.415 539.1316) 
(list 3445.415 538.9546) 
(list 3519.4375 538.3046)))
(apply 'command (append '("pline") coords '("c")))
(setq currobj (ssadd (entlast) currobj))
(setq coords (list 
(list 3519.4375 538.1616) 
(list 3445.415 538.8116) 
(list 3445.415 538.6346) 
(list 3519.4375 538.0846)))
(apply 'command (append '("pline") coords '("c")))
(setq currobj (ssadd (entlast) currobj))
(setq coords (list 
(list 3519.4375 537.9416) 
(list 3445.415 538.4916) 
(list 3445.415 538.3146) 
(list 3519.4375 537.8646)))
(apply 'command (append '("pline") coords '("c")))
(setq currobj (ssadd (entlast) currobj))
(setq coords (list 
(list 3519.4375 537.7216) 
(list 3445.415 538.1716) 
(list 3445.415 537.9946) 
(list 3519.4375 537.6446)))
(apply 'command (append '("pline") coords '("c")))
(setq currobj (ssadd (entlast) currobj))
(setq coords (list 
(list 3519.4375 537.5016) 
(list 3445.415 537.8516) 
(list 3445.415 537.6746) 
(list 3519.4375 537.4246)))
(apply 'command (append '("pline") coords '("c")))
(setq currobj (ssadd (entlast) currobj))
(setq coords (list 
(list 3519.4375 537.2816) 
(list 3445.415 537.5316) 
(list 3445.415 537.3546) 
(list 3519.4375 537.2046)))
(apply 'command (append '("pline") coords '("c")))
(setq currobj (ssadd (entlast) currobj))
(setq coords (list 
(list 3519.4375 537.0616) 
(list 3445.415 537.2116) 
(list 3445.415 537.0346) 
(list 3519.4375 536.9846)))
(apply 'command (append '("pline") coords '("c")))
(setq currobj (ssadd (entlast) currobj))
(setq coords (list 
(list 3519.4375 536.8416) 
(list 3445.415 536.8916) 
(list 3445.415 536.7146) 
(list 3519.4375 536.7646)))
(apply 'command (append '("pline") coords '("c")))
(setq currobj (ssadd (entlast) currobj))
(setq coords (list 
(list 3519.4375 536.6216) 
(list 3445.415 536.5716) 
(list 3445.415 536.3946) 
(list 3519.4375 536.5446)))
(apply 'command (append '("pline") coords '("c")))
(setq currobj (ssadd (entlast) currobj))
(setq coords (list 
(list 3519.4375 536.4016) 
(list 3445.415 536.2516) 
(list 3445.415 536.0746) 
(list 3519.4375 536.3246)))
(apply 'command (append '("pline") coords '("c")))
(setq currobj (ssadd (entlast) currobj))
(setq coords (list 
(list 3519.4375 536.1816) 
(list 3445.415 535.9316) 
(list 3445.415 535.7546) 
(list 3519.4375 536.1046)))
(apply 'command (append '("pline") coords '("c")))
(setq currobj (ssadd (entlast) currobj))
(setq coords (list 
(list 3519.4375 535.9616) 
(list 3445.415 535.6116) 
(list 3445.415 535.4346) 
(list 3519.4375 535.8846)))
(apply 'command (append '("pline") coords '("c")))
(setq currobj (ssadd (entlast) currobj))
(setq coords (list 
(list 3519.4375 535.7416) 
(list 3445.415 535.2916) 
(list 3445.415 535.1146) 
(list 3519.4375 535.6646)))
(apply 'command (append '("pline") coords '("c")))
(setq currobj (ssadd (entlast) currobj))
(setq coords (list 
(list 3519.4375 535.5216) 
(list 3445.415 534.9716) 
(list 3445.415 534.7946) 
(list 3519.4375 535.4446)))
(apply 'command (append '("pline") coords '("c")))
(setq currobj (ssadd (entlast) currobj))
(setq coords (list 
(list 3519.4375 535.3016) 
(list 3445.415 534.6516) 
(list 3445.415 534.4746) 
(list 3519.4375 535.2246)))
(apply 'command (append '("pline") coords '("c")))
(setq currobj (ssadd (entlast) currobj))
(command "_layer" "set" "nitride" "")
(command "_layer" "set" "text" "")
(command "_circle" "3519.0625,524.0816" "0.075")
(command "_circle" "3519.0625,524.3816" "0.075")
(command "_circle" "3519.0625,524.6816" "0.075")
(command "_circle" "3519.0625,524.9816" "0.075")
(command "_circle" "3519.0625,525.2816" "0.075")
(command "_circle" "3518.7625,524.0816" "0.075")
(command "_circle" "3518.7625,524.3816" "0.075")
(command "_circle" "3518.7625,524.6816" "0.075")
(command "_circle" "3518.7625,524.9816" "0.075")
(command "_circle" "3518.7625,525.2816" "0.075")
(command "_circle" "3518.4625,524.0816" "0.075")
(command "_circle" "3518.4625,524.3816" "0.075")
(command "_circle" "3518.4625,524.6816" "0.075")
(command "_circle" "3518.4625,524.9816" "0.075")
(command "_circle" "3518.4625,525.2816" "0.075")
(command "_circle" "3518.1625,524.0816" "0.075")
(command "_circle" "3518.1625,524.3816" "0.075")
(command "_circle" "3518.1625,524.6816" "0.075")
(command "_circle" "3518.1625,524.9816" "0.075")
(command "_circle" "3518.1625,525.2816" "0.075")
(command "_circle" "3517.8625,524.0816" "0.075")
(command "_circle" "3517.8625,524.3816" "0.075")
(command "_circle" "3517.8625,524.6816" "0.075")
(command "_circle" "3517.8625,524.9816" "0.075")
(command "_circle" "3517.8625,525.2816" "0.075")
(command "_layer" "set" "nitride" "")
(setq coords (list 
(list 3520.2625 549.5246) 
(list 3520.2625 665.1693) 
(list 3519.7375 665.1693) 
(list 3519.7375 549.5246)))
(apply 'command (append '("pline") coords '("c")))
(setq currobj (ssadd (entlast) currobj))
(command "_layer" "set" "prebias" "")
(command "_rectangle" "3519.7375,549.5246" "3520.2625,665.1693")
(setq currobj (ssadd (entlast) currobj))
(command "_layer" "set" "nitride" "")
(setq coords (list 
(list 3520.2625 665.1693) 
(list 3520.5625 675.1693) 
(list 3520.5625 675.1693) 
(list 3520.5625 676.1693) 
(list 3594.585 675.4193) 
(list 3594.585 680.3623) 
(list 3520.5625 679.6123) 
(list 3520.5625 680.6123) 
(list 3520.5625 680.6123) 
(list 3520.2625 690.6123) 
(list 3519.7375 690.6123) 
(list 3519.4375 680.6123) 
(list 3519.4375 680.6123) 
(list 3519.4375 679.6123) 
(list 3445.415 680.3623) 
(list 3445.415 675.4193) 
(list 3519.4375 676.1693) 
(list 3519.4375 675.1693) 
(list 3519.4375 675.1693) 
(list 3519.7375 665.1693)))
(apply 'command (append '("pline") coords '("c")))
(setq currobj (ssadd (entlast) currobj))
(command "_layer" "set" "prebias" "")
(setq coords (list 
(list 3519.4375 665.1693) 
(list 3519.4375 676.1693) 
(list 3445.415 675.4193) 
(list 3445.415 680.3623) 
(list 3519.4375 679.6123) 
(list 3519.4375 690.6123) 
(list 3520.5625 690.6123) 
(list 3520.5625 679.6123) 
(list 3594.585 680.3623) 
(list 3594.585 675.4193) 
(list 3520.5625 676.1693) 
(list 3520.5625 665.1693)))
(apply 'command (append '("pline") coords '("c")))
(setq currobj (ssadd (entlast) currobj))
(command "_layer" "set" "nitride" "")
(command "_layer" "set" "fda1" "")
(setq coords (list 
(list 3520.5625 676.3123) 
(list 3594.585 675.5623) 
(list 3594.585 675.7393) 
(list 3520.5625 676.3893)))
(apply 'command (append '("pline") coords '("c")))
(setq currobj (ssadd (entlast) currobj))
(setq coords (list 
(list 3520.5625 676.5323) 
(list 3594.585 675.8823) 
(list 3594.585 676.0593) 
(list 3520.5625 676.6093)))
(apply 'command (append '("pline") coords '("c")))
(setq currobj (ssadd (entlast) currobj))
(setq coords (list 
(list 3520.5625 676.7523) 
(list 3594.585 676.2023) 
(list 3594.585 676.3793) 
(list 3520.5625 676.8293)))
(apply 'command (append '("pline") coords '("c")))
(setq currobj (ssadd (entlast) currobj))
(setq coords (list 
(list 3520.5625 676.9723) 
(list 3594.585 676.5223) 
(list 3594.585 676.6993) 
(list 3520.5625 677.0493)))
(apply 'command (append '("pline") coords '("c")))
(setq currobj (ssadd (entlast) currobj))
(setq coords (list 
(list 3520.5625 677.1923) 
(list 3594.585 676.8423) 
(list 3594.585 677.0193) 
(list 3520.5625 677.2693)))
(apply 'command (append '("pline") coords '("c")))
(setq currobj (ssadd (entlast) currobj))
(setq coords (list 
(list 3520.5625 677.4123) 
(list 3594.585 677.1623) 
(list 3594.585 677.3393) 
(list 3520.5625 677.4893)))
(apply 'command (append '("pline") coords '("c")))
(setq currobj (ssadd (entlast) currobj))
(setq coords (list 
(list 3520.5625 677.6323) 
(list 3594.585 677.4823) 
(list 3594.585 677.6593) 
(list 3520.5625 677.7093)))
(apply 'command (append '("pline") coords '("c")))
(setq currobj (ssadd (entlast) currobj))
(setq coords (list 
(list 3520.5625 677.8523) 
(list 3594.585 677.8023) 
(list 3594.585 677.9793) 
(list 3520.5625 677.9293)))
(apply 'command (append '("pline") coords '("c")))
(setq currobj (ssadd (entlast) currobj))
(setq coords (list 
(list 3520.5625 678.0723) 
(list 3594.585 678.1223) 
(list 3594.585 678.2993) 
(list 3520.5625 678.1493)))
(apply 'command (append '("pline") coords '("c")))
(setq currobj (ssadd (entlast) currobj))
(setq coords (list 
(list 3520.5625 678.2923) 
(list 3594.585 678.4423) 
(list 3594.585 678.6193) 
(list 3520.5625 678.3693)))
(apply 'command (append '("pline") coords '("c")))
(setq currobj (ssadd (entlast) currobj))
(setq coords (list 
(list 3520.5625 678.5123) 
(list 3594.585 678.7623) 
(list 3594.585 678.9393) 
(list 3520.5625 678.5893)))
(apply 'command (append '("pline") coords '("c")))
(setq currobj (ssadd (entlast) currobj))
(setq coords (list 
(list 3520.5625 678.7323) 
(list 3594.585 679.0823) 
(list 3594.585 679.2593) 
(list 3520.5625 678.8093)))
(apply 'command (append '("pline") coords '("c")))
(setq currobj (ssadd (entlast) currobj))
(setq coords (list 
(list 3520.5625 678.9523) 
(list 3594.585 679.4023) 
(list 3594.585 679.5793) 
(list 3520.5625 679.0293)))
(apply 'command (append '("pline") coords '("c")))
(setq currobj (ssadd (entlast) currobj))
(setq coords (list 
(list 3520.5625 679.1723) 
(list 3594.585 679.7223) 
(list 3594.585 679.8993) 
(list 3520.5625 679.2493)))
(apply 'command (append '("pline") coords '("c")))
(setq currobj (ssadd (entlast) currobj))
(setq coords (list 
(list 3520.5625 679.3923) 
(list 3594.585 680.0423) 
(list 3594.585 680.2193) 
(list 3520.5625 679.4693)))
(apply 'command (append '("pline") coords '("c")))
(setq currobj (ssadd (entlast) currobj))
(setq coords (list 
(list 3519.4375 679.4693) 
(list 3445.415 680.2193) 
(list 3445.415 680.0423) 
(list 3519.4375 679.3923)))
(apply 'command (append '("pline") coords '("c")))
(setq currobj (ssadd (entlast) currobj))
(setq coords (list 
(list 3519.4375 679.2493) 
(list 3445.415 679.8993) 
(list 3445.415 679.7223) 
(list 3519.4375 679.1723)))
(apply 'command (append '("pline") coords '("c")))
(setq currobj (ssadd (entlast) currobj))
(setq coords (list 
(list 3519.4375 679.0293) 
(list 3445.415 679.5793) 
(list 3445.415 679.4023) 
(list 3519.4375 678.9523)))
(apply 'command (append '("pline") coords '("c")))
(setq currobj (ssadd (entlast) currobj))
(setq coords (list 
(list 3519.4375 678.8093) 
(list 3445.415 679.2593) 
(list 3445.415 679.0823) 
(list 3519.4375 678.7323)))
(apply 'command (append '("pline") coords '("c")))
(setq currobj (ssadd (entlast) currobj))
(setq coords (list 
(list 3519.4375 678.5893) 
(list 3445.415 678.9393) 
(list 3445.415 678.7623) 
(list 3519.4375 678.5123)))
(apply 'command (append '("pline") coords '("c")))
(setq currobj (ssadd (entlast) currobj))
(setq coords (list 
(list 3519.4375 678.3693) 
(list 3445.415 678.6193) 
(list 3445.415 678.4423) 
(list 3519.4375 678.2923)))
(apply 'command (append '("pline") coords '("c")))
(setq currobj (ssadd (entlast) currobj))
(setq coords (list 
(list 3519.4375 678.1493) 
(list 3445.415 678.2993) 
(list 3445.415 678.1223) 
(list 3519.4375 678.0723)))
(apply 'command (append '("pline") coords '("c")))
(setq currobj (ssadd (entlast) currobj))
(setq coords (list 
(list 3519.4375 677.9293) 
(list 3445.415 677.9793) 
(list 3445.415 677.8023) 
(list 3519.4375 677.8523)))
(apply 'command (append '("pline") coords '("c")))
(setq currobj (ssadd (entlast) currobj))
(setq coords (list 
(list 3519.4375 677.7093) 
(list 3445.415 677.6593) 
(list 3445.415 677.4823) 
(list 3519.4375 677.6323)))
(apply 'command (append '("pline") coords '("c")))
(setq currobj (ssadd (entlast) currobj))
(setq coords (list 
(list 3519.4375 677.4893) 
(list 3445.415 677.3393) 
(list 3445.415 677.1623) 
(list 3519.4375 677.4123)))
(apply 'command (append '("pline") coords '("c")))
(setq currobj (ssadd (entlast) currobj))
(setq coords (list 
(list 3519.4375 677.2693) 
(list 3445.415 677.0193) 
(list 3445.415 676.8423) 
(list 3519.4375 677.1923)))
(apply 'command (append '("pline") coords '("c")))
(setq currobj (ssadd (entlast) currobj))
(setq coords (list 
(list 3519.4375 677.0493) 
(list 3445.415 676.6993) 
(list 3445.415 676.5223) 
(list 3519.4375 676.9723)))
(apply 'command (append '("pline") coords '("c")))
(setq currobj (ssadd (entlast) currobj))
(setq coords (list 
(list 3519.4375 676.8293) 
(list 3445.415 676.3793) 
(list 3445.415 676.2023) 
(list 3519.4375 676.7523)))
(apply 'command (append '("pline") coords '("c")))
(setq currobj (ssadd (entlast) currobj))
(setq coords (list 
(list 3519.4375 676.6093) 
(list 3445.415 676.0593) 
(list 3445.415 675.8823) 
(list 3519.4375 676.5323)))
(apply 'command (append '("pline") coords '("c")))
(setq currobj (ssadd (entlast) currobj))
(setq coords (list 
(list 3519.4375 676.3893) 
(list 3445.415 675.7393) 
(list 3445.415 675.5623) 
(list 3519.4375 676.3123)))
(apply 'command (append '("pline") coords '("c")))
(setq currobj (ssadd (entlast) currobj))
(command "_layer" "set" "nitride" "")
(command "_layer" "set" "text" "")
(command "_circle" "3519.0625,665.1693" "0.075")
(command "_circle" "3519.0625,665.4693" "0.075")
(command "_circle" "3519.0625,665.7693" "0.075")
(command "_circle" "3519.0625,666.0693" "0.075")
(command "_circle" "3519.0625,666.3693" "0.075")
(command "_circle" "3518.7625,665.1693" "0.075")
(command "_circle" "3518.7625,665.4693" "0.075")
(command "_circle" "3518.7625,665.7693" "0.075")
(command "_circle" "3518.7625,666.0693" "0.075")
(command "_circle" "3518.7625,666.3693" "0.075")
(command "_circle" "3518.4625,665.1693" "0.075")
(command "_circle" "3518.4625,665.4693" "0.075")
(command "_circle" "3518.4625,665.7693" "0.075")
(command "_circle" "3518.4625,666.0693" "0.075")
(command "_circle" "3518.4625,666.3693" "0.075")
(command "_circle" "3518.1625,665.1693" "0.075")
(command "_circle" "3518.1625,665.4693" "0.075")
(command "_circle" "3518.1625,665.7693" "0.075")
(command "_circle" "3518.1625,666.0693" "0.075")
(command "_circle" "3518.1625,666.3693" "0.075")
(command "_circle" "3517.8625,665.1693" "0.075")
(command "_circle" "3517.8625,665.4693" "0.075")
(command "_circle" "3517.8625,665.7693" "0.075")
(command "_circle" "3517.8625,666.0693" "0.075")
(command "_circle" "3517.8625,666.3693" "0.075")
(command "_layer" "set" "nitride" "")
(setq coords (list 
(list 3520.2625 690.6123) 
(list 3520.2625 806.257) 
(list 3519.7375 806.257) 
(list 3519.7375 690.6123)))
(apply 'command (append '("pline") coords '("c")))
(setq currobj (ssadd (entlast) currobj))
(command "_layer" "set" "prebias" "")
(command "_rectangle" "3519.7375,690.6123" "3520.2625,806.257")
(setq currobj (ssadd (entlast) currobj))
(command "_layer" "set" "nitride" "")
(setq coords (list 
(list 3520.2625 806.257) 
(list 3520.5625 816.257) 
(list 3520.5625 816.257) 
(list 3520.5625 817.257) 
(list 3594.585 816.507) 
(list 3594.585 821.45) 
(list 3520.5625 820.7) 
(list 3520.5625 821.7) 
(list 3520.5625 821.7) 
(list 3520.2625 831.7) 
(list 3519.7375 831.7) 
(list 3519.4375 821.7) 
(list 3519.4375 821.7) 
(list 3519.4375 820.7) 
(list 3445.415 821.45) 
(list 3445.415 816.507) 
(list 3519.4375 817.257) 
(list 3519.4375 816.257) 
(list 3519.4375 816.257) 
(list 3519.7375 806.257)))
(apply 'command (append '("pline") coords '("c")))
(setq currobj (ssadd (entlast) currobj))
(command "_layer" "set" "prebias" "")
(setq coords (list 
(list 3519.4375 806.257) 
(list 3519.4375 817.257) 
(list 3445.415 816.507) 
(list 3445.415 821.45) 
(list 3519.4375 820.7) 
(list 3519.4375 831.7) 
(list 3520.5625 831.7) 
(list 3520.5625 820.7) 
(list 3594.585 821.45) 
(list 3594.585 816.507) 
(list 3520.5625 817.257) 
(list 3520.5625 806.257)))
(apply 'command (append '("pline") coords '("c")))
(setq currobj (ssadd (entlast) currobj))
(command "_layer" "set" "nitride" "")
(command "_layer" "set" "fda1" "")
(setq coords (list 
(list 3520.5625 817.4) 
(list 3594.585 816.65) 
(list 3594.585 816.827) 
(list 3520.5625 817.477)))
(apply 'command (append '("pline") coords '("c")))
(setq currobj (ssadd (entlast) currobj))
(setq coords (list 
(list 3520.5625 817.62) 
(list 3594.585 816.97) 
(list 3594.585 817.147) 
(list 3520.5625 817.697)))
(apply 'command (append '("pline") coords '("c")))
(setq currobj (ssadd (entlast) currobj))
(setq coords (list 
(list 3520.5625 817.84) 
(list 3594.585 817.29) 
(list 3594.585 817.467) 
(list 3520.5625 817.917)))
(apply 'command (append '("pline") coords '("c")))
(setq currobj (ssadd (entlast) currobj))
(setq coords (list 
(list 3520.5625 818.06) 
(list 3594.585 817.61) 
(list 3594.585 817.787) 
(list 3520.5625 818.137)))
(apply 'command (append '("pline") coords '("c")))
(setq currobj (ssadd (entlast) currobj))
(setq coords (list 
(list 3520.5625 818.28) 
(list 3594.585 817.93) 
(list 3594.585 818.107) 
(list 3520.5625 818.357)))
(apply 'command (append '("pline") coords '("c")))
(setq currobj (ssadd (entlast) currobj))
(setq coords (list 
(list 3520.5625 818.5) 
(list 3594.585 818.25) 
(list 3594.585 818.427) 
(list 3520.5625 818.577)))
(apply 'command (append '("pline") coords '("c")))
(setq currobj (ssadd (entlast) currobj))
(setq coords (list 
(list 3520.5625 818.72) 
(list 3594.585 818.57) 
(list 3594.585 818.747) 
(list 3520.5625 818.797)))
(apply 'command (append '("pline") coords '("c")))
(setq currobj (ssadd (entlast) currobj))
(setq coords (list 
(list 3520.5625 818.94) 
(list 3594.585 818.89) 
(list 3594.585 819.067) 
(list 3520.5625 819.017)))
(apply 'command (append '("pline") coords '("c")))
(setq currobj (ssadd (entlast) currobj))
(setq coords (list 
(list 3520.5625 819.16) 
(list 3594.585 819.21) 
(list 3594.585 819.387) 
(list 3520.5625 819.237)))
(apply 'command (append '("pline") coords '("c")))
(setq currobj (ssadd (entlast) currobj))
(setq coords (list 
(list 3520.5625 819.38) 
(list 3594.585 819.53) 
(list 3594.585 819.707) 
(list 3520.5625 819.457)))
(apply 'command (append '("pline") coords '("c")))
(setq currobj (ssadd (entlast) currobj))
(setq coords (list 
(list 3520.5625 819.6) 
(list 3594.585 819.85) 
(list 3594.585 820.027) 
(list 3520.5625 819.677)))
(apply 'command (append '("pline") coords '("c")))
(setq currobj (ssadd (entlast) currobj))
(setq coords (list 
(list 3520.5625 819.82) 
(list 3594.585 820.17) 
(list 3594.585 820.347) 
(list 3520.5625 819.897)))
(apply 'command (append '("pline") coords '("c")))
(setq currobj (ssadd (entlast) currobj))
(setq coords (list 
(list 3520.5625 820.04) 
(list 3594.585 820.49) 
(list 3594.585 820.667) 
(list 3520.5625 820.117)))
(apply 'command (append '("pline") coords '("c")))
(setq currobj (ssadd (entlast) currobj))
(setq coords (list 
(list 3520.5625 820.26) 
(list 3594.585 820.81) 
(list 3594.585 820.987) 
(list 3520.5625 820.337)))
(apply 'command (append '("pline") coords '("c")))
(setq currobj (ssadd (entlast) currobj))
(setq coords (list 
(list 3520.5625 820.48) 
(list 3594.585 821.13) 
(list 3594.585 821.307) 
(list 3520.5625 820.557)))
(apply 'command (append '("pline") coords '("c")))
(setq currobj (ssadd (entlast) currobj))
(setq coords (list 
(list 3519.4375 820.557) 
(list 3445.415 821.307) 
(list 3445.415 821.13) 
(list 3519.4375 820.48)))
(apply 'command (append '("pline") coords '("c")))
(setq currobj (ssadd (entlast) currobj))
(setq coords (list 
(list 3519.4375 820.337) 
(list 3445.415 820.987) 
(list 3445.415 820.81) 
(list 3519.4375 820.26)))
(apply 'command (append '("pline") coords '("c")))
(setq currobj (ssadd (entlast) currobj))
(setq coords (list 
(list 3519.4375 820.117) 
(list 3445.415 820.667) 
(list 3445.415 820.49) 
(list 3519.4375 820.04)))
(apply 'command (append '("pline") coords '("c")))
(setq currobj (ssadd (entlast) currobj))
(setq coords (list 
(list 3519.4375 819.897) 
(list 3445.415 820.347) 
(list 3445.415 820.17) 
(list 3519.4375 819.82)))
(apply 'command (append '("pline") coords '("c")))
(setq currobj (ssadd (entlast) currobj))
(setq coords (list 
(list 3519.4375 819.677) 
(list 3445.415 820.027) 
(list 3445.415 819.85) 
(list 3519.4375 819.6)))
(apply 'command (append '("pline") coords '("c")))
(setq currobj (ssadd (entlast) currobj))
(setq coords (list 
(list 3519.4375 819.457) 
(list 3445.415 819.707) 
(list 3445.415 819.53) 
(list 3519.4375 819.38)))
(apply 'command (append '("pline") coords '("c")))
(setq currobj (ssadd (entlast) currobj))
(setq coords (list 
(list 3519.4375 819.237) 
(list 3445.415 819.387) 
(list 3445.415 819.21) 
(list 3519.4375 819.16)))
(apply 'command (append '("pline") coords '("c")))
(setq currobj (ssadd (entlast) currobj))
(setq coords (list 
(list 3519.4375 819.017) 
(list 3445.415 819.067) 
(list 3445.415 818.89) 
(list 3519.4375 818.94)))
(apply 'command (append '("pline") coords '("c")))
(setq currobj (ssadd (entlast) currobj))
(setq coords (list 
(list 3519.4375 818.797) 
(list 3445.415 818.747) 
(list 3445.415 818.57) 
(list 3519.4375 818.72)))
(apply 'command (append '("pline") coords '("c")))
(setq currobj (ssadd (entlast) currobj))
(setq coords (list 
(list 3519.4375 818.577) 
(list 3445.415 818.427) 
(list 3445.415 818.25) 
(list 3519.4375 818.5)))
(apply 'command (append '("pline") coords '("c")))
(setq currobj (ssadd (entlast) currobj))
(setq coords (list 
(list 3519.4375 818.357) 
(list 3445.415 818.107) 
(list 3445.415 817.93) 
(list 3519.4375 818.28)))
(apply 'command (append '("pline") coords '("c")))
(setq currobj (ssadd (entlast) currobj))
(setq coords (list 
(list 3519.4375 818.137) 
(list 3445.415 817.787) 
(list 3445.415 817.61) 
(list 3519.4375 818.06)))
(apply 'command (append '("pline") coords '("c")))
(setq currobj (ssadd (entlast) currobj))
(setq coords (list 
(list 3519.4375 817.917) 
(list 3445.415 817.467) 
(list 3445.415 817.29) 
(list 3519.4375 817.84)))
(apply 'command (append '("pline") coords '("c")))
(setq currobj (ssadd (entlast) currobj))
(setq coords (list 
(list 3519.4375 817.697) 
(list 3445.415 817.147) 
(list 3445.415 816.97) 
(list 3519.4375 817.62)))
(apply 'command (append '("pline") coords '("c")))
(setq currobj (ssadd (entlast) currobj))
(setq coords (list 
(list 3519.4375 817.477) 
(list 3445.415 816.827) 
(list 3445.415 816.65) 
(list 3519.4375 817.4)))
(apply 'command (append '("pline") coords '("c")))
(setq currobj (ssadd (entlast) currobj))
(command "_layer" "set" "nitride" "")
(command "_layer" "set" "text" "")
(command "_circle" "3519.0625,806.257" "0.075")
(command "_circle" "3519.0625,806.557" "0.075")
(command "_circle" "3519.0625,806.857" "0.075")
(command "_circle" "3519.0625,807.157" "0.075")
(command "_circle" "3519.0625,807.457" "0.075")
(command "_circle" "3518.7625,806.257" "0.075")
(command "_circle" "3518.7625,806.557" "0.075")
(command "_circle" "3518.7625,806.857" "0.075")
(command "_circle" "3518.7625,807.157" "0.075")
(command "_circle" "3518.7625,807.457" "0.075")
(command "_circle" "3518.4625,806.257" "0.075")
(command "_circle" "3518.4625,806.557" "0.075")
(command "_circle" "3518.4625,806.857" "0.075")
(command "_circle" "3518.4625,807.157" "0.075")
(command "_circle" "3518.4625,807.457" "0.075")
(command "_circle" "3518.1625,806.257" "0.075")
(command "_circle" "3518.1625,806.557" "0.075")
(command "_circle" "3518.1625,806.857" "0.075")
(command "_circle" "3518.1625,807.157" "0.075")
(command "_circle" "3518.1625,807.457" "0.075")
(command "_circle" "3517.8625,806.257" "0.075")
(command "_circle" "3517.8625,806.557" "0.075")
(command "_circle" "3517.8625,806.857" "0.075")
(command "_circle" "3517.8625,807.157" "0.075")
(command "_circle" "3517.8625,807.457" "0.075")
(command "_layer" "set" "nitride" "")
(setq coords (list 
(list 3520.2625 831.7) 
(list 3520.2625 836.7) 
(list 3519.7375 836.7) 
(list 3519.7375 831.7)))
(apply 'command (append '("pline") coords '("c")))
(setq currobj (ssadd (entlast) currobj))
(command "_layer" "set" "prebias" "")
(command "_rectangle" "3519.7375,831.7" "3520.2625,836.7")
(setq currobj (ssadd (entlast) currobj))
(command "_layer" "set" "nitride" "")
(setq cooledsinglenanobeam11 currobj)
(setq currobj nil)
(setq currobj (ssadd))
; DRAWING PHOTONIC CRYSTAL
(command "_layer" "set" "negYjunc" "")
(setq coords (list 
(list 3520.125 866.7) 
(list 3520 851.7) 
(list 3520 866.7)))
(apply 'command (append '("pline") coords '("c")))
(setq currobj (ssadd (entlast) currobj))
(setq coords (list 
(list 3520.2625 836.7) 
(list 3520.405 866.7) 
(list 3521.122 866.7) 
(list 3521.122 836.7)))
(apply 'command (append '("pline") coords '("c")))
(setq currobj (ssadd (entlast) currobj))
(setq coords (list 
(list 3519.875 866.7) 
(list 3520 851.7) 
(list 3520 866.7)))
(apply 'command (append '("pline") coords '("c")))
(setq currobj (ssadd (entlast) currobj))
(setq coords (list 
(list 3519.7375 836.7) 
(list 3519.595 866.7) 
(list 3518.878 866.7) 
(list 3518.878 836.7)))
(apply 'command (append '("pline") coords '("c")))
(setq currobj (ssadd (entlast) currobj))
(command "_layer" "set" "nitride" "")
(setq yjunction11 currobj)
(setq currobj nil)
(setq currobj (ssadd))
(setq tap11 nil)
(setq tap11 (ssadd))
(command "_layer" "set" "phc" "")
(setq coords (list 
(list 3520 866.7) 
(list 3520.125 866.7) 
(list 3520.125 866.7103) 
(list 3520.125 866.7206) 
(list 3520.125 866.7308) 
(list 3520.125 866.7411) 
(list 3520.125 866.7514) 
(list 3520.125 866.7617) 
(list 3520.125 866.7719) 
(list 3520.125 866.7822) 
(list 3520.125 866.7925) 
(list 3520.125 866.8028) 
(list 3520.125 866.8131) 
(list 3520.125 866.8233) 
(list 3520.125 866.8336) 
(list 3520.125 866.8439) 
(list 3520.125 866.8542) 
(list 3520.125 866.8644) 
(list 3520.125 866.8747) 
(list 3520.125 866.885) 
(list 3520.125 866.8953) 
(list 3520.125 866.9056) 
(list 3520.125 866.9158) 
(list 3520.125 866.9261) 
(list 3520.125 866.9364) 
(list 3520.125 866.9467) 
(list 3520.125 866.9569) 
(list 3520.125 866.9672) 
(list 3520.125 866.9775) 
(list 3520.125 866.9878) 
(list 3520.125 866.9981) 
(list 3520.125 867.0083) 
(list 3520.125 867.0186) 
(list 3520.125 867.0289) 
(list 3520.125 867.0392) 
(list 3520.125 867.0494) 
(list 3520.125 867.0597) 
(list 3520.125 867.07) 
(list 3520 867.07)))
(apply 'command (append '("pline") coords '("c")))
(setq tap11 (ssadd (entlast) tap11))
(command "_mirror" (entlast) "" "3520,900" "3520,901" "No")
(setq tap11 (ssadd (entlast) tap11))
(setq coords (list 
(list 3520.4154 866.7) 
(list 3520.405 866.7) 
(list 3520.4053 866.7103) 
(list 3520.4055 866.7206) 
(list 3520.4058 866.7308) 
(list 3520.4059 866.7411) 
(list 3520.406 866.7514) 
(list 3520.406 866.7617) 
(list 3520.4059 866.7719) 
(list 3520.4056 866.7822) 
(list 3520.4053 866.7925) 
(list 3520.4049 866.8028) 
(list 3520.4044 866.8131) 
(list 3520.4039 866.8233) 
(list 3520.4033 866.8336) 
(list 3520.4028 866.8439) 
(list 3520.4022 866.8542) 
(list 3520.4017 866.8644) 
(list 3520.4014 866.8747) 
(list 3520.4011 866.885) 
(list 3520.4009 866.8953) 
(list 3520.4009 866.9056) 
(list 3520.4011 866.9158) 
(list 3520.4015 866.9261) 
(list 3520.4021 866.9364) 
(list 3520.4028 866.9467) 
(list 3520.4037 866.9569) 
(list 3520.4048 866.9672) 
(list 3520.4059 866.9775) 
(list 3520.4072 866.9878) 
(list 3520.4085 866.9981) 
(list 3520.4099 867.0083) 
(list 3520.4111 867.0186) 
(list 3520.4123 867.0289) 
(list 3520.4134 867.0392) 
(list 3520.4143 867.0494) 
(list 3520.415 867.0597) 
(list 3520.4154 867.07) 
(list 3520.4154 867.07)))
(apply 'command (append '("pline") coords '("c")))
(setq tap11 (ssadd (entlast) tap11))
(command "_mirror" (entlast) "" "3520,900" "3520,901" "No")
(setq tap11 (ssadd (entlast) tap11))
(setq coords (list 
(list 3521.122 866.7) 
(list 3520.4154 866.7) 
(list 3520.4154 866.7103) 
(list 3520.4154 866.7206) 
(list 3520.4154 866.7308) 
(list 3520.4154 866.7411) 
(list 3520.4154 866.7514) 
(list 3520.4154 866.7617) 
(list 3520.4154 866.7719) 
(list 3520.4154 866.7822) 
(list 3520.4154 866.7925) 
(list 3520.4154 866.8028) 
(list 3520.4154 866.8131) 
(list 3520.4154 866.8233) 
(list 3520.4154 866.8336) 
(list 3520.4154 866.8439) 
(list 3520.4154 866.8542) 
(list 3520.4154 866.8644) 
(list 3520.4154 866.8747) 
(list 3520.4154 866.885) 
(list 3520.4154 866.8953) 
(list 3520.4154 866.9056) 
(list 3520.4154 866.9158) 
(list 3520.4154 866.9261) 
(list 3520.4154 866.9364) 
(list 3520.4154 866.9467) 
(list 3520.4154 866.9569) 
(list 3520.4154 866.9672) 
(list 3520.4154 866.9775) 
(list 3520.4154 866.9878) 
(list 3520.4154 866.9981) 
(list 3520.4154 867.0083) 
(list 3520.4154 867.0186) 
(list 3520.4154 867.0289) 
(list 3520.4154 867.0392) 
(list 3520.4154 867.0494) 
(list 3520.4154 867.0597) 
(list 3520.4154 867.07) 
(list 3521.122 867.07)))
(apply 'command (append '("pline") coords '("c")))
(setq tap11 (ssadd (entlast) tap11))
(command "_mirror" (entlast) "" "3520,900" "3520,901" "No")
(setq tap11 (ssadd (entlast) tap11))
(setq coords (list 
(list 3520 867.07) 
(list 3520.125 867.07) 
(list 3520.125 867.0803) 
(list 3520.125 867.0906) 
(list 3520.125 867.1008) 
(list 3520.125 867.1111) 
(list 3520.125 867.1214) 
(list 3520.125 867.1317) 
(list 3520.125 867.1419) 
(list 3520.125 867.1522) 
(list 3520.125 867.1625) 
(list 3520.125 867.1728) 
(list 3520.125 867.1831) 
(list 3520.125 867.1933) 
(list 3520.125 867.2036) 
(list 3520.125 867.2139) 
(list 3520.125 867.2242) 
(list 3520.125 867.2344) 
(list 3520.125 867.2447) 
(list 3520.125 867.255) 
(list 3520.125 867.2653) 
(list 3520.125 867.2756) 
(list 3520.125 867.2858) 
(list 3520.125 867.2961) 
(list 3520.125 867.3064) 
(list 3520.125 867.3167) 
(list 3520.125 867.3269) 
(list 3520.125 867.3372) 
(list 3520.125 867.3475) 
(list 3520.125 867.3578) 
(list 3520.125 867.3681) 
(list 3520.125 867.3783) 
(list 3520.125 867.3886) 
(list 3520.125 867.3989) 
(list 3520.125 867.4092) 
(list 3520.125 867.4194) 
(list 3520.125 867.4297) 
(list 3520.125 867.44) 
(list 3520 867.44)))
(apply 'command (append '("pline") coords '("c")))
(setq tap11 (ssadd (entlast) tap11))
(command "_mirror" (entlast) "" "3520,900" "3520,901" "No")
(setq tap11 (ssadd (entlast) tap11))
(setq coords (list 
(list 3520.4258 867.07) 
(list 3520.4154 867.07) 
(list 3520.4155 867.0803) 
(list 3520.4154 867.0906) 
(list 3520.4149 867.1008) 
(list 3520.4142 867.1111) 
(list 3520.4131 867.1214) 
(list 3520.4118 867.1317) 
(list 3520.4102 867.1419) 
(list 3520.4085 867.1522) 
(list 3520.4066 867.1625) 
(list 3520.4046 867.1728) 
(list 3520.4026 867.1831) 
(list 3520.4006 867.1933) 
(list 3520.3987 867.2036) 
(list 3520.397 867.2139) 
(list 3520.3956 867.2242) 
(list 3520.3944 867.2344) 
(list 3520.3936 867.2447) 
(list 3520.3932 867.255) 
(list 3520.3932 867.2653) 
(list 3520.3936 867.2756) 
(list 3520.3945 867.2858) 
(list 3520.3958 867.2961) 
(list 3520.3975 867.3064) 
(list 3520.3995 867.3167) 
(list 3520.4019 867.3269) 
(list 3520.4044 867.3372) 
(list 3520.4072 867.3475) 
(list 3520.4101 867.3578) 
(list 3520.4129 867.3681) 
(list 3520.4157 867.3783) 
(list 3520.4183 867.3886) 
(list 3520.4206 867.3989) 
(list 3520.4226 867.4092) 
(list 3520.4242 867.4194) 
(list 3520.4252 867.4297) 
(list 3520.4258 867.44) 
(list 3520.4258 867.44)))
(apply 'command (append '("pline") coords '("c")))
(setq tap11 (ssadd (entlast) tap11))
(command "_mirror" (entlast) "" "3520,900" "3520,901" "No")
(setq tap11 (ssadd (entlast) tap11))
(setq coords (list 
(list 3521.122 867.07) 
(list 3520.4258 867.07) 
(list 3520.4258 867.0803) 
(list 3520.4258 867.0906) 
(list 3520.4258 867.1008) 
(list 3520.4258 867.1111) 
(list 3520.4258 867.1214) 
(list 3520.4258 867.1317) 
(list 3520.4258 867.1419) 
(list 3520.4258 867.1522) 
(list 3520.4258 867.1625) 
(list 3520.4258 867.1728) 
(list 3520.4258 867.1831) 
(list 3520.4258 867.1933) 
(list 3520.4258 867.2036) 
(list 3520.4258 867.2139) 
(list 3520.4258 867.2242) 
(list 3520.4258 867.2344) 
(list 3520.4258 867.2447) 
(list 3520.4258 867.255) 
(list 3520.4258 867.2653) 
(list 3520.4258 867.2756) 
(list 3520.4258 867.2858) 
(list 3520.4258 867.2961) 
(list 3520.4258 867.3064) 
(list 3520.4258 867.3167) 
(list 3520.4258 867.3269) 
(list 3520.4258 867.3372) 
(list 3520.4258 867.3475) 
(list 3520.4258 867.3578) 
(list 3520.4258 867.3681) 
(list 3520.4258 867.3783) 
(list 3520.4258 867.3886) 
(list 3520.4258 867.3989) 
(list 3520.4258 867.4092) 
(list 3520.4258 867.4194) 
(list 3520.4258 867.4297) 
(list 3520.4258 867.44) 
(list 3521.122 867.44)))
(apply 'command (append '("pline") coords '("c")))
(setq tap11 (ssadd (entlast) tap11))
(command "_mirror" (entlast) "" "3520,900" "3520,901" "No")
(setq tap11 (ssadd (entlast) tap11))
(setq coords (list 
(list 3520 867.44) 
(list 3520.125 867.44) 
(list 3520.125 867.4503) 
(list 3520.125 867.4606) 
(list 3520.125 867.4708) 
(list 3520.125 867.4811) 
(list 3520.125 867.4914) 
(list 3520.125 867.5017) 
(list 3520.125 867.5119) 
(list 3520.125 867.5222) 
(list 3520.125 867.5325) 
(list 3520.125 867.5428) 
(list 3520.125 867.5531) 
(list 3520.125 867.5633) 
(list 3520.125 867.5736) 
(list 3520.125 867.5839) 
(list 3520.125 867.5942) 
(list 3520.125 867.6044) 
(list 3520.125 867.6147) 
(list 3520.125 867.625) 
(list 3520.125 867.6353) 
(list 3520.125 867.6456) 
(list 3520.125 867.6558) 
(list 3520.125 867.6661) 
(list 3520.125 867.6764) 
(list 3520.125 867.6867) 
(list 3520.125 867.6969) 
(list 3520.125 867.7072) 
(list 3520.125 867.7175) 
(list 3520.125 867.7278) 
(list 3520.125 867.7381) 
(list 3520.125 867.7483) 
(list 3520.125 867.7586) 
(list 3520.125 867.7689) 
(list 3520.125 867.7792) 
(list 3520.125 867.7894) 
(list 3520.125 867.7997) 
(list 3520.125 867.81) 
(list 3520 867.81)))
(apply 'command (append '("pline") coords '("c")))
(setq tap11 (ssadd (entlast) tap11))
(command "_mirror" (entlast) "" "3520,900" "3520,901" "No")
(setq tap11 (ssadd (entlast) tap11))
(setq coords (list 
(list 3520.4362 867.44) 
(list 3520.4258 867.44) 
(list 3520.4258 867.4503) 
(list 3520.4252 867.4606) 
(list 3520.4241 867.4708) 
(list 3520.4224 867.4811) 
(list 3520.4203 867.4914) 
(list 3520.4176 867.5017) 
(list 3520.4146 867.5119) 
(list 3520.4113 867.5222) 
(list 3520.4079 867.5325) 
(list 3520.4043 867.5428) 
(list 3520.4007 867.5531) 
(list 3520.3973 867.5633) 
(list 3520.3941 867.5736) 
(list 3520.3913 867.5839) 
(list 3520.3889 867.5942) 
(list 3520.3871 867.6044) 
(list 3520.3859 867.6147) 
(list 3520.3853 867.625) 
(list 3520.3855 867.6353) 
(list 3520.3863 867.6456) 
(list 3520.3878 867.6558) 
(list 3520.39 867.6661) 
(list 3520.3929 867.6764) 
(list 3520.3962 867.6867) 
(list 3520.4 867.6969) 
(list 3520.4041 867.7072) 
(list 3520.4085 867.7175) 
(list 3520.4129 867.7278) 
(list 3520.4173 867.7381) 
(list 3520.4215 867.7483) 
(list 3520.4254 867.7586) 
(list 3520.4289 867.7689) 
(list 3520.4318 867.7792) 
(list 3520.434 867.7894) 
(list 3520.4355 867.7997) 
(list 3520.4362 867.81) 
(list 3520.4362 867.81)))
(apply 'command (append '("pline") coords '("c")))
(setq tap11 (ssadd (entlast) tap11))
(command "_mirror" (entlast) "" "3520,900" "3520,901" "No")
(setq tap11 (ssadd (entlast) tap11))
(setq coords (list 
(list 3521.122 867.44) 
(list 3520.4362 867.44) 
(list 3520.4362 867.4503) 
(list 3520.4362 867.4606) 
(list 3520.4362 867.4708) 
(list 3520.4362 867.4811) 
(list 3520.4362 867.4914) 
(list 3520.4362 867.5017) 
(list 3520.4362 867.5119) 
(list 3520.4362 867.5222) 
(list 3520.4362 867.5325) 
(list 3520.4362 867.5428) 
(list 3520.4362 867.5531) 
(list 3520.4362 867.5633) 
(list 3520.4362 867.5736) 
(list 3520.4362 867.5839) 
(list 3520.4362 867.5942) 
(list 3520.4362 867.6044) 
(list 3520.4362 867.6147) 
(list 3520.4362 867.625) 
(list 3520.4362 867.6353) 
(list 3520.4362 867.6456) 
(list 3520.4362 867.6558) 
(list 3520.4362 867.6661) 
(list 3520.4362 867.6764) 
(list 3520.4362 867.6867) 
(list 3520.4362 867.6969) 
(list 3520.4362 867.7072) 
(list 3520.4362 867.7175) 
(list 3520.4362 867.7278) 
(list 3520.4362 867.7381) 
(list 3520.4362 867.7483) 
(list 3520.4362 867.7586) 
(list 3520.4362 867.7689) 
(list 3520.4362 867.7792) 
(list 3520.4362 867.7894) 
(list 3520.4362 867.7997) 
(list 3520.4362 867.81) 
(list 3521.122 867.81)))
(apply 'command (append '("pline") coords '("c")))
(setq tap11 (ssadd (entlast) tap11))
(command "_mirror" (entlast) "" "3520,900" "3520,901" "No")
(setq tap11 (ssadd (entlast) tap11))
(setq coords (list 
(list 3520 867.81) 
(list 3520.125 867.81) 
(list 3520.125 867.8203) 
(list 3520.125 867.8306) 
(list 3520.125 867.8408) 
(list 3520.125 867.8511) 
(list 3520.125 867.8614) 
(list 3520.125 867.8717) 
(list 3520.125 867.8819) 
(list 3520.125 867.8922) 
(list 3520.125 867.9025) 
(list 3520.125 867.9128) 
(list 3520.125 867.9231) 
(list 3520.125 867.9333) 
(list 3520.125 867.9436) 
(list 3520.125 867.9539) 
(list 3520.125 867.9642) 
(list 3520.125 867.9744) 
(list 3520.125 867.9847) 
(list 3520.125 867.995) 
(list 3520.125 868.0053) 
(list 3520.125 868.0156) 
(list 3520.125 868.0258) 
(list 3520.125 868.0361) 
(list 3520.125 868.0464) 
(list 3520.125 868.0567) 
(list 3520.125 868.0669) 
(list 3520.125 868.0772) 
(list 3520.125 868.0875) 
(list 3520.125 868.0978) 
(list 3520.125 868.1081) 
(list 3520.125 868.1183) 
(list 3520.125 868.1286) 
(list 3520.125 868.1389) 
(list 3520.125 868.1492) 
(list 3520.125 868.1594) 
(list 3520.125 868.1697) 
(list 3520.125 868.18) 
(list 3520 868.18)))
(apply 'command (append '("pline") coords '("c")))
(setq tap11 (ssadd (entlast) tap11))
(command "_mirror" (entlast) "" "3520,900" "3520,901" "No")
(setq tap11 (ssadd (entlast) tap11))
(setq coords (list 
(list 3520.4466 867.81) 
(list 3520.4362 867.81) 
(list 3520.4361 867.8203) 
(list 3520.4351 867.8306) 
(list 3520.4333 867.8408) 
(list 3520.4307 867.8511) 
(list 3520.4274 867.8614) 
(list 3520.4235 867.8717) 
(list 3520.419 867.8819) 
(list 3520.4142 867.8922) 
(list 3520.4091 867.9025) 
(list 3520.404 867.9128) 
(list 3520.3989 867.9231) 
(list 3520.394 867.9333) 
(list 3520.3895 867.9436) 
(list 3520.3856 867.9539) 
(list 3520.3823 867.9642) 
(list 3520.3798 867.9744) 
(list 3520.3782 867.9847) 
(list 3520.3775 867.995) 
(list 3520.3777 868.0053) 
(list 3520.379 868.0156) 
(list 3520.3812 868.0258) 
(list 3520.3843 868.0361) 
(list 3520.3882 868.0464) 
(list 3520.3929 868.0567) 
(list 3520.3981 868.0669) 
(list 3520.4038 868.0772) 
(list 3520.4097 868.0875) 
(list 3520.4158 868.0978) 
(list 3520.4217 868.1081) 
(list 3520.4274 868.1183) 
(list 3520.4326 868.1286) 
(list 3520.4371 868.1389) 
(list 3520.4409 868.1492) 
(list 3520.4439 868.1594) 
(list 3520.4458 868.1697) 
(list 3520.4466 868.18) 
(list 3520.4466 868.18)))
(apply 'command (append '("pline") coords '("c")))
(setq tap11 (ssadd (entlast) tap11))
(command "_mirror" (entlast) "" "3520,900" "3520,901" "No")
(setq tap11 (ssadd (entlast) tap11))
(setq coords (list 
(list 3521.122 867.81) 
(list 3520.4466 867.81) 
(list 3520.4466 867.8203) 
(list 3520.4466 867.8306) 
(list 3520.4466 867.8408) 
(list 3520.4466 867.8511) 
(list 3520.4466 867.8614) 
(list 3520.4466 867.8717) 
(list 3520.4466 867.8819) 
(list 3520.4466 867.8922) 
(list 3520.4466 867.9025) 
(list 3520.4466 867.9128) 
(list 3520.4466 867.9231) 
(list 3520.4466 867.9333) 
(list 3520.4466 867.9436) 
(list 3520.4466 867.9539) 
(list 3520.4466 867.9642) 
(list 3520.4466 867.9744) 
(list 3520.4466 867.9847) 
(list 3520.4466 867.995) 
(list 3520.4466 868.0053) 
(list 3520.4466 868.0156) 
(list 3520.4466 868.0258) 
(list 3520.4466 868.0361) 
(list 3520.4466 868.0464) 
(list 3520.4466 868.0567) 
(list 3520.4466 868.0669) 
(list 3520.4466 868.0772) 
(list 3520.4466 868.0875) 
(list 3520.4466 868.0978) 
(list 3520.4466 868.1081) 
(list 3520.4466 868.1183) 
(list 3520.4466 868.1286) 
(list 3520.4466 868.1389) 
(list 3520.4466 868.1492) 
(list 3520.4466 868.1594) 
(list 3520.4466 868.1697) 
(list 3520.4466 868.18) 
(list 3521.122 868.18)))
(apply 'command (append '("pline") coords '("c")))
(setq tap11 (ssadd (entlast) tap11))
(command "_mirror" (entlast) "" "3520,900" "3520,901" "No")
(setq tap11 (ssadd (entlast) tap11))
(setq coords (list 
(list 3520 868.18) 
(list 3520.125 868.18) 
(list 3520.125 868.1903) 
(list 3520.125 868.2006) 
(list 3520.125 868.2108) 
(list 3520.125 868.2211) 
(list 3520.125 868.2314) 
(list 3520.125 868.2417) 
(list 3520.125 868.2519) 
(list 3520.125 868.2622) 
(list 3520.125 868.2725) 
(list 3520.125 868.2828) 
(list 3520.125 868.2931) 
(list 3520.125 868.3033) 
(list 3520.125 868.3136) 
(list 3520.125 868.3239) 
(list 3520.125 868.3342) 
(list 3520.125 868.3444) 
(list 3520.125 868.3547) 
(list 3520.125 868.365) 
(list 3520.125 868.3753) 
(list 3520.125 868.3856) 
(list 3520.125 868.3958) 
(list 3520.125 868.4061) 
(list 3520.125 868.4164) 
(list 3520.125 868.4267) 
(list 3520.125 868.4369) 
(list 3520.125 868.4472) 
(list 3520.125 868.4575) 
(list 3520.125 868.4678) 
(list 3520.125 868.4781) 
(list 3520.125 868.4883) 
(list 3520.125 868.4986) 
(list 3520.125 868.5089) 
(list 3520.125 868.5192) 
(list 3520.125 868.5294) 
(list 3520.125 868.5397) 
(list 3520.125 868.55) 
(list 3520 868.55)))
(apply 'command (append '("pline") coords '("c")))
(setq tap11 (ssadd (entlast) tap11))
(command "_mirror" (entlast) "" "3520,900" "3520,901" "No")
(setq tap11 (ssadd (entlast) tap11))
(setq coords (list 
(list 3520.457 868.18) 
(list 3520.4466 868.18) 
(list 3520.4463 868.1903) 
(list 3520.4449 868.2006) 
(list 3520.4425 868.2108) 
(list 3520.439 868.2211) 
(list 3520.4345 868.2314) 
(list 3520.4293 868.2417) 
(list 3520.4234 868.2519) 
(list 3520.417 868.2622) 
(list 3520.4104 868.2725) 
(list 3520.4036 868.2828) 
(list 3520.397 868.2931) 
(list 3520.3907 868.3033) 
(list 3520.3849 868.3136) 
(list 3520.3799 868.3239) 
(list 3520.3757 868.3342) 
(list 3520.3725 868.3444) 
(list 3520.3704 868.3547) 
(list 3520.3696 868.365) 
(list 3520.37 868.3753) 
(list 3520.3717 868.3856) 
(list 3520.3746 868.3958) 
(list 3520.3786 868.4061) 
(list 3520.3836 868.4164) 
(list 3520.3896 868.4267) 
(list 3520.3963 868.4369) 
(list 3520.4035 868.4472) 
(list 3520.411 868.4575) 
(list 3520.4186 868.4678) 
(list 3520.4261 868.4781) 
(list 3520.4332 868.4883) 
(list 3520.4397 868.4986) 
(list 3520.4454 868.5089) 
(list 3520.4501 868.5192) 
(list 3520.4537 868.5294) 
(list 3520.456 868.5397) 
(list 3520.457 868.55) 
(list 3520.457 868.55)))
(apply 'command (append '("pline") coords '("c")))
(setq tap11 (ssadd (entlast) tap11))
(command "_mirror" (entlast) "" "3520,900" "3520,901" "No")
(setq tap11 (ssadd (entlast) tap11))
(setq coords (list 
(list 3521.122 868.18) 
(list 3520.457 868.18) 
(list 3520.457 868.1903) 
(list 3520.457 868.2006) 
(list 3520.457 868.2108) 
(list 3520.457 868.2211) 
(list 3520.457 868.2314) 
(list 3520.457 868.2417) 
(list 3520.457 868.2519) 
(list 3520.457 868.2622) 
(list 3520.457 868.2725) 
(list 3520.457 868.2828) 
(list 3520.457 868.2931) 
(list 3520.457 868.3033) 
(list 3520.457 868.3136) 
(list 3520.457 868.3239) 
(list 3520.457 868.3342) 
(list 3520.457 868.3444) 
(list 3520.457 868.3547) 
(list 3520.457 868.365) 
(list 3520.457 868.3753) 
(list 3520.457 868.3856) 
(list 3520.457 868.3958) 
(list 3520.457 868.4061) 
(list 3520.457 868.4164) 
(list 3520.457 868.4267) 
(list 3520.457 868.4369) 
(list 3520.457 868.4472) 
(list 3520.457 868.4575) 
(list 3520.457 868.4678) 
(list 3520.457 868.4781) 
(list 3520.457 868.4883) 
(list 3520.457 868.4986) 
(list 3520.457 868.5089) 
(list 3520.457 868.5192) 
(list 3520.457 868.5294) 
(list 3520.457 868.5397) 
(list 3520.457 868.55) 
(list 3521.122 868.55)))
(apply 'command (append '("pline") coords '("c")))
(setq tap11 (ssadd (entlast) tap11))
(command "_mirror" (entlast) "" "3520,900" "3520,901" "No")
(setq tap11 (ssadd (entlast) tap11))
(setq coords (list 
(list 3520 868.55) 
(list 3520.125 868.55) 
(list 3520.125 868.5603) 
(list 3520.125 868.5706) 
(list 3520.125 868.5808) 
(list 3520.125 868.5911) 
(list 3520.125 868.6014) 
(list 3520.125 868.6117) 
(list 3520.125 868.6219) 
(list 3520.125 868.6322) 
(list 3520.125 868.6425) 
(list 3520.125 868.6528) 
(list 3520.125 868.6631) 
(list 3520.125 868.6733) 
(list 3520.125 868.6836) 
(list 3520.125 868.6939) 
(list 3520.125 868.7042) 
(list 3520.125 868.7144) 
(list 3520.125 868.7247) 
(list 3520.125 868.735) 
(list 3520.125 868.7453) 
(list 3520.125 868.7556) 
(list 3520.125 868.7658) 
(list 3520.125 868.7761) 
(list 3520.125 868.7864) 
(list 3520.125 868.7967) 
(list 3520.125 868.8069) 
(list 3520.125 868.8172) 
(list 3520.125 868.8275) 
(list 3520.125 868.8378) 
(list 3520.125 868.8481) 
(list 3520.125 868.8583) 
(list 3520.125 868.8686) 
(list 3520.125 868.8789) 
(list 3520.125 868.8892) 
(list 3520.125 868.8994) 
(list 3520.125 868.9097) 
(list 3520.125 868.92) 
(list 3520 868.92)))
(apply 'command (append '("pline") coords '("c")))
(setq tap11 (ssadd (entlast) tap11))
(command "_mirror" (entlast) "" "3520,900" "3520,901" "No")
(setq tap11 (ssadd (entlast) tap11))
(setq coords (list 
(list 3520.4674 868.55) 
(list 3520.457 868.55) 
(list 3520.4566 868.5603) 
(list 3520.4548 868.5706) 
(list 3520.4516 868.5808) 
(list 3520.4472 868.5911) 
(list 3520.4417 868.6014) 
(list 3520.4351 868.6117) 
(list 3520.4278 868.6219) 
(list 3520.4199 868.6322) 
(list 3520.4117 868.6425) 
(list 3520.4033 868.6528) 
(list 3520.3951 868.6631) 
(list 3520.3874 868.6733) 
(list 3520.3803 868.6836) 
(list 3520.3741 868.6939) 
(list 3520.369 868.7042) 
(list 3520.3652 868.7144) 
(list 3520.3627 868.7247) 
(list 3520.3617 868.735) 
(list 3520.3623 868.7453) 
(list 3520.3644 868.7556) 
(list 3520.3679 868.7658) 
(list 3520.3728 868.7761) 
(list 3520.379 868.7864) 
(list 3520.3863 868.7967) 
(list 3520.3944 868.8069) 
(list 3520.4032 868.8172) 
(list 3520.4123 868.8275) 
(list 3520.4215 868.8378) 
(list 3520.4305 868.8481) 
(list 3520.439 868.8583) 
(list 3520.4468 868.8686) 
(list 3520.4537 868.8789) 
(list 3520.4593 868.8892) 
(list 3520.4635 868.8994) 
(list 3520.4663 868.9097) 
(list 3520.4674 868.92) 
(list 3520.4674 868.92)))
(apply 'command (append '("pline") coords '("c")))
(setq tap11 (ssadd (entlast) tap11))
(command "_mirror" (entlast) "" "3520,900" "3520,901" "No")
(setq tap11 (ssadd (entlast) tap11))
(setq coords (list 
(list 3521.122 868.55) 
(list 3520.4674 868.55) 
(list 3520.4674 868.5603) 
(list 3520.4674 868.5706) 
(list 3520.4674 868.5808) 
(list 3520.4674 868.5911) 
(list 3520.4674 868.6014) 
(list 3520.4674 868.6117) 
(list 3520.4674 868.6219) 
(list 3520.4674 868.6322) 
(list 3520.4674 868.6425) 
(list 3520.4674 868.6528) 
(list 3520.4674 868.6631) 
(list 3520.4674 868.6733) 
(list 3520.4674 868.6836) 
(list 3520.4674 868.6939) 
(list 3520.4674 868.7042) 
(list 3520.4674 868.7144) 
(list 3520.4674 868.7247) 
(list 3520.4674 868.735) 
(list 3520.4674 868.7453) 
(list 3520.4674 868.7556) 
(list 3520.4674 868.7658) 
(list 3520.4674 868.7761) 
(list 3520.4674 868.7864) 
(list 3520.4674 868.7967) 
(list 3520.4674 868.8069) 
(list 3520.4674 868.8172) 
(list 3520.4674 868.8275) 
(list 3520.4674 868.8378) 
(list 3520.4674 868.8481) 
(list 3520.4674 868.8583) 
(list 3520.4674 868.8686) 
(list 3520.4674 868.8789) 
(list 3520.4674 868.8892) 
(list 3520.4674 868.8994) 
(list 3520.4674 868.9097) 
(list 3520.4674 868.92) 
(list 3521.122 868.92)))
(apply 'command (append '("pline") coords '("c")))
(setq tap11 (ssadd (entlast) tap11))
(command "_mirror" (entlast) "" "3520,900" "3520,901" "No")
(setq tap11 (ssadd (entlast) tap11))
(setq coords (list 
(list 3520 868.92) 
(list 3520.125 868.92) 
(list 3520.125 868.9303) 
(list 3520.125 868.9406) 
(list 3520.125 868.9508) 
(list 3520.125 868.9611) 
(list 3520.125 868.9714) 
(list 3520.125 868.9817) 
(list 3520.125 868.9919) 
(list 3520.125 869.0022) 
(list 3520.125 869.0125) 
(list 3520.125 869.0228) 
(list 3520.125 869.0331) 
(list 3520.125 869.0433) 
(list 3520.125 869.0536) 
(list 3520.125 869.0639) 
(list 3520.125 869.0742) 
(list 3520.125 869.0844) 
(list 3520.125 869.0947) 
(list 3520.125 869.105) 
(list 3520.125 869.1153) 
(list 3520.125 869.1256) 
(list 3520.125 869.1358) 
(list 3520.125 869.1461) 
(list 3520.125 869.1564) 
(list 3520.125 869.1667) 
(list 3520.125 869.1769) 
(list 3520.125 869.1872) 
(list 3520.125 869.1975) 
(list 3520.125 869.2078) 
(list 3520.125 869.2181) 
(list 3520.125 869.2283) 
(list 3520.125 869.2386) 
(list 3520.125 869.2489) 
(list 3520.125 869.2592) 
(list 3520.125 869.2694) 
(list 3520.125 869.2797) 
(list 3520.125 869.29) 
(list 3520 869.29)))
(apply 'command (append '("pline") coords '("c")))
(setq tap11 (ssadd (entlast) tap11))
(command "_mirror" (entlast) "" "3520,900" "3520,901" "No")
(setq tap11 (ssadd (entlast) tap11))
(setq coords (list 
(list 3520.4778 868.92) 
(list 3520.4674 868.92) 
(list 3520.4669 868.9303) 
(list 3520.4646 868.9406) 
(list 3520.4608 868.9508) 
(list 3520.4555 868.9611) 
(list 3520.4488 868.9714) 
(list 3520.441 868.9817) 
(list 3520.4322 868.9919) 
(list 3520.4228 869.0022) 
(list 3520.4129 869.0125) 
(list 3520.403 869.0228) 
(list 3520.3933 869.0331) 
(list 3520.3841 869.0433) 
(list 3520.3757 869.0536) 
(list 3520.3684 869.0639) 
(list 3520.3624 869.0742) 
(list 3520.3579 869.0844) 
(list 3520.355 869.0947) 
(list 3520.3539 869.105) 
(list 3520.3546 869.1153) 
(list 3520.357 869.1256) 
(list 3520.3613 869.1358) 
(list 3520.3671 869.1461) 
(list 3520.3744 869.1564) 
(list 3520.383 869.1667) 
(list 3520.3926 869.1769) 
(list 3520.4029 869.1872) 
(list 3520.4136 869.1975) 
(list 3520.4243 869.2078) 
(list 3520.4349 869.2181) 
(list 3520.4449 869.2283) 
(list 3520.454 869.2386) 
(list 3520.4619 869.2489) 
(list 3520.4685 869.2592) 
(list 3520.4734 869.2694) 
(list 3520.4765 869.2797) 
(list 3520.4778 869.29) 
(list 3520.4778 869.29)))
(apply 'command (append '("pline") coords '("c")))
(setq tap11 (ssadd (entlast) tap11))
(command "_mirror" (entlast) "" "3520,900" "3520,901" "No")
(setq tap11 (ssadd (entlast) tap11))
(setq coords (list 
(list 3521.122 868.92) 
(list 3520.4778 868.92) 
(list 3520.4778 868.9303) 
(list 3520.4778 868.9406) 
(list 3520.4778 868.9508) 
(list 3520.4778 868.9611) 
(list 3520.4778 868.9714) 
(list 3520.4778 868.9817) 
(list 3520.4778 868.9919) 
(list 3520.4778 869.0022) 
(list 3520.4778 869.0125) 
(list 3520.4778 869.0228) 
(list 3520.4778 869.0331) 
(list 3520.4778 869.0433) 
(list 3520.4778 869.0536) 
(list 3520.4778 869.0639) 
(list 3520.4778 869.0742) 
(list 3520.4778 869.0844) 
(list 3520.4778 869.0947) 
(list 3520.4778 869.105) 
(list 3520.4778 869.1153) 
(list 3520.4778 869.1256) 
(list 3520.4778 869.1358) 
(list 3520.4778 869.1461) 
(list 3520.4778 869.1564) 
(list 3520.4778 869.1667) 
(list 3520.4778 869.1769) 
(list 3520.4778 869.1872) 
(list 3520.4778 869.1975) 
(list 3520.4778 869.2078) 
(list 3520.4778 869.2181) 
(list 3520.4778 869.2283) 
(list 3520.4778 869.2386) 
(list 3520.4778 869.2489) 
(list 3520.4778 869.2592) 
(list 3520.4778 869.2694) 
(list 3520.4778 869.2797) 
(list 3520.4778 869.29) 
(list 3521.122 869.29)))
(apply 'command (append '("pline") coords '("c")))
(setq tap11 (ssadd (entlast) tap11))
(command "_mirror" (entlast) "" "3520,900" "3520,901" "No")
(setq tap11 (ssadd (entlast) tap11))
(setq coords (list 
(list 3520 869.29) 
(list 3520.125 869.29) 
(list 3520.125 869.3003) 
(list 3520.125 869.3106) 
(list 3520.125 869.3208) 
(list 3520.125 869.3311) 
(list 3520.125 869.3414) 
(list 3520.125 869.3517) 
(list 3520.125 869.3619) 
(list 3520.125 869.3722) 
(list 3520.125 869.3825) 
(list 3520.125 869.3928) 
(list 3520.125 869.4031) 
(list 3520.125 869.4133) 
(list 3520.125 869.4236) 
(list 3520.125 869.4339) 
(list 3520.125 869.4442) 
(list 3520.125 869.4544) 
(list 3520.125 869.4647) 
(list 3520.125 869.475) 
(list 3520.125 869.4853) 
(list 3520.125 869.4956) 
(list 3520.125 869.5058) 
(list 3520.125 869.5161) 
(list 3520.125 869.5264) 
(list 3520.125 869.5367) 
(list 3520.125 869.5469) 
(list 3520.125 869.5572) 
(list 3520.125 869.5675) 
(list 3520.125 869.5778) 
(list 3520.125 869.5881) 
(list 3520.125 869.5983) 
(list 3520.125 869.6086) 
(list 3520.125 869.6189) 
(list 3520.125 869.6292) 
(list 3520.125 869.6394) 
(list 3520.125 869.6497) 
(list 3520.125 869.66) 
(list 3520 869.66)))
(apply 'command (append '("pline") coords '("c")))
(setq tap11 (ssadd (entlast) tap11))
(command "_mirror" (entlast) "" "3520,900" "3520,901" "No")
(setq tap11 (ssadd (entlast) tap11))
(setq coords (list 
(list 3520.4882 869.29) 
(list 3520.4778 869.29) 
(list 3520.4771 869.3003) 
(list 3520.4745 869.3106) 
(list 3520.47 869.3208) 
(list 3520.4638 869.3311) 
(list 3520.456 869.3414) 
(list 3520.4468 869.3517) 
(list 3520.4366 869.3619) 
(list 3520.4256 869.3722) 
(list 3520.4142 869.3825) 
(list 3520.4027 869.3928) 
(list 3520.3914 869.4031) 
(list 3520.3808 869.4133) 
(list 3520.3711 869.4236) 
(list 3520.3627 869.4339) 
(list 3520.3557 869.4442) 
(list 3520.3505 869.4544) 
(list 3520.3473 869.4647) 
(list 3520.346 869.475) 
(list 3520.3468 869.4853) 
(list 3520.3497 869.4956) 
(list 3520.3546 869.5058) 
(list 3520.3614 869.5161) 
(list 3520.3698 869.5264) 
(list 3520.3797 869.5367) 
(list 3520.3907 869.5469) 
(list 3520.4025 869.5572) 
(list 3520.4148 869.5675) 
(list 3520.4272 869.5778) 
(list 3520.4393 869.5881) 
(list 3520.4507 869.5983) 
(list 3520.4611 869.6086) 
(list 3520.4702 869.6189) 
(list 3520.4776 869.6292) 
(list 3520.4832 869.6394) 
(list 3520.4868 869.6497) 
(list 3520.4882 869.66) 
(list 3520.4882 869.66)))
(apply 'command (append '("pline") coords '("c")))
(setq tap11 (ssadd (entlast) tap11))
(command "_mirror" (entlast) "" "3520,900" "3520,901" "No")
(setq tap11 (ssadd (entlast) tap11))
(setq coords (list 
(list 3521.122 869.29) 
(list 3520.4882 869.29) 
(list 3520.4882 869.3003) 
(list 3520.4882 869.3106) 
(list 3520.4882 869.3208) 
(list 3520.4882 869.3311) 
(list 3520.4882 869.3414) 
(list 3520.4882 869.3517) 
(list 3520.4882 869.3619) 
(list 3520.4882 869.3722) 
(list 3520.4882 869.3825) 
(list 3520.4882 869.3928) 
(list 3520.4882 869.4031) 
(list 3520.4882 869.4133) 
(list 3520.4882 869.4236) 
(list 3520.4882 869.4339) 
(list 3520.4882 869.4442) 
(list 3520.4882 869.4544) 
(list 3520.4882 869.4647) 
(list 3520.4882 869.475) 
(list 3520.4882 869.4853) 
(list 3520.4882 869.4956) 
(list 3520.4882 869.5058) 
(list 3520.4882 869.5161) 
(list 3520.4882 869.5264) 
(list 3520.4882 869.5367) 
(list 3520.4882 869.5469) 
(list 3520.4882 869.5572) 
(list 3520.4882 869.5675) 
(list 3520.4882 869.5778) 
(list 3520.4882 869.5881) 
(list 3520.4882 869.5983) 
(list 3520.4882 869.6086) 
(list 3520.4882 869.6189) 
(list 3520.4882 869.6292) 
(list 3520.4882 869.6394) 
(list 3520.4882 869.6497) 
(list 3520.4882 869.66) 
(list 3521.122 869.66)))
(apply 'command (append '("pline") coords '("c")))
(setq tap11 (ssadd (entlast) tap11))
(command "_mirror" (entlast) "" "3520,900" "3520,901" "No")
(setq tap11 (ssadd (entlast) tap11))
(setq coords (list 
(list 3520 869.66) 
(list 3520.125 869.66) 
(list 3520.125 869.6703) 
(list 3520.125 869.6806) 
(list 3520.125 869.6908) 
(list 3520.125 869.7011) 
(list 3520.125 869.7114) 
(list 3520.125 869.7217) 
(list 3520.125 869.7319) 
(list 3520.125 869.7422) 
(list 3520.125 869.7525) 
(list 3520.125 869.7628) 
(list 3520.125 869.7731) 
(list 3520.125 869.7833) 
(list 3520.125 869.7936) 
(list 3520.125 869.8039) 
(list 3520.125 869.8142) 
(list 3520.125 869.8244) 
(list 3520.125 869.8347) 
(list 3520.125 869.845) 
(list 3520.125 869.8553) 
(list 3520.125 869.8656) 
(list 3520.125 869.8758) 
(list 3520.125 869.8861) 
(list 3520.125 869.8964) 
(list 3520.125 869.9067) 
(list 3520.125 869.9169) 
(list 3520.125 869.9272) 
(list 3520.125 869.9375) 
(list 3520.125 869.9478) 
(list 3520.125 869.9581) 
(list 3520.125 869.9683) 
(list 3520.125 869.9786) 
(list 3520.125 869.9889) 
(list 3520.125 869.9992) 
(list 3520.125 870.0094) 
(list 3520.125 870.0197) 
(list 3520.125 870.03) 
(list 3520 870.03)))
(apply 'command (append '("pline") coords '("c")))
(setq tap11 (ssadd (entlast) tap11))
(command "_mirror" (entlast) "" "3520,900" "3520,901" "No")
(setq tap11 (ssadd (entlast) tap11))
(setq coords (list 
(list 3520.4986 869.66) 
(list 3520.4882 869.66) 
(list 3520.4874 869.6703) 
(list 3520.4843 869.6806) 
(list 3520.4792 869.6908) 
(list 3520.472 869.7011) 
(list 3520.4631 869.7114) 
(list 3520.4526 869.7217) 
(list 3520.441 869.7319) 
(list 3520.4285 869.7422) 
(list 3520.4154 869.7525) 
(list 3520.4024 869.7628) 
(list 3520.3896 869.7731) 
(list 3520.3775 869.7833) 
(list 3520.3665 869.7936) 
(list 3520.3569 869.8039) 
(list 3520.3491 869.8142) 
(list 3520.3432 869.8244) 
(list 3520.3395 869.8347) 
(list 3520.3381 869.845) 
(list 3520.3391 869.8553) 
(list 3520.3424 869.8656) 
(list 3520.348 869.8758) 
(list 3520.3557 869.8861) 
(list 3520.3652 869.8964) 
(list 3520.3764 869.9067) 
(list 3520.3889 869.9169) 
(list 3520.4022 869.9272) 
(list 3520.4161 869.9375) 
(list 3520.43 869.9478) 
(list 3520.4437 869.9581) 
(list 3520.4565 869.9683) 
(list 3520.4682 869.9786) 
(list 3520.4785 869.9889) 
(list 3520.4868 869.9992) 
(list 3520.4931 870.0094) 
(list 3520.4971 870.0197) 
(list 3520.4986 870.03) 
(list 3520.4986 870.03)))
(apply 'command (append '("pline") coords '("c")))
(setq tap11 (ssadd (entlast) tap11))
(command "_mirror" (entlast) "" "3520,900" "3520,901" "No")
(setq tap11 (ssadd (entlast) tap11))
(setq coords (list 
(list 3521.122 869.66) 
(list 3520.4986 869.66) 
(list 3520.4986 869.6703) 
(list 3520.4986 869.6806) 
(list 3520.4986 869.6908) 
(list 3520.4986 869.7011) 
(list 3520.4986 869.7114) 
(list 3520.4986 869.7217) 
(list 3520.4986 869.7319) 
(list 3520.4986 869.7422) 
(list 3520.4986 869.7525) 
(list 3520.4986 869.7628) 
(list 3520.4986 869.7731) 
(list 3520.4986 869.7833) 
(list 3520.4986 869.7936) 
(list 3520.4986 869.8039) 
(list 3520.4986 869.8142) 
(list 3520.4986 869.8244) 
(list 3520.4986 869.8347) 
(list 3520.4986 869.845) 
(list 3520.4986 869.8553) 
(list 3520.4986 869.8656) 
(list 3520.4986 869.8758) 
(list 3520.4986 869.8861) 
(list 3520.4986 869.8964) 
(list 3520.4986 869.9067) 
(list 3520.4986 869.9169) 
(list 3520.4986 869.9272) 
(list 3520.4986 869.9375) 
(list 3520.4986 869.9478) 
(list 3520.4986 869.9581) 
(list 3520.4986 869.9683) 
(list 3520.4986 869.9786) 
(list 3520.4986 869.9889) 
(list 3520.4986 869.9992) 
(list 3520.4986 870.0094) 
(list 3520.4986 870.0197) 
(list 3520.4986 870.03) 
(list 3521.122 870.03)))
(apply 'command (append '("pline") coords '("c")))
(setq tap11 (ssadd (entlast) tap11))
(command "_mirror" (entlast) "" "3520,900" "3520,901" "No")
(setq tap11 (ssadd (entlast) tap11))
(setq coords (list 
(list 3520 870.03) 
(list 3520.125 870.03) 
(list 3520.125 870.0403) 
(list 3520.125 870.0506) 
(list 3520.125 870.0608) 
(list 3520.125 870.0711) 
(list 3520.125 870.0814) 
(list 3520.125 870.0917) 
(list 3520.125 870.1019) 
(list 3520.125 870.1122) 
(list 3520.125 870.1225) 
(list 3520.125 870.1328) 
(list 3520.125 870.1431) 
(list 3520.125 870.1533) 
(list 3520.125 870.1636) 
(list 3520.125 870.1739) 
(list 3520.125 870.1842) 
(list 3520.125 870.1944) 
(list 3520.125 870.2047) 
(list 3520.125 870.215) 
(list 3520.125 870.2253) 
(list 3520.125 870.2356) 
(list 3520.125 870.2458) 
(list 3520.125 870.2561) 
(list 3520.125 870.2664) 
(list 3520.125 870.2767) 
(list 3520.125 870.2869) 
(list 3520.125 870.2972) 
(list 3520.125 870.3075) 
(list 3520.125 870.3178) 
(list 3520.125 870.3281) 
(list 3520.125 870.3383) 
(list 3520.125 870.3486) 
(list 3520.125 870.3589) 
(list 3520.125 870.3692) 
(list 3520.125 870.3794) 
(list 3520.125 870.3897) 
(list 3520.125 870.4) 
(list 3520 870.4)))
(apply 'command (append '("pline") coords '("c")))
(setq tap11 (ssadd (entlast) tap11))
(command "_mirror" (entlast) "" "3520,900" "3520,901" "No")
(setq tap11 (ssadd (entlast) tap11))
(setq coords (list 
(list 3520.509 870.03) 
(list 3520.4986 870.03) 
(list 3520.4976 870.0403) 
(list 3520.4942 870.0506) 
(list 3520.4884 870.0608) 
(list 3520.4803 870.0711) 
(list 3520.4702 870.0814) 
(list 3520.4585 870.0917) 
(list 3520.4454 870.1019) 
(list 3520.4313 870.1122) 
(list 3520.4167 870.1225) 
(list 3520.402 870.1328) 
(list 3520.3877 870.1431) 
(list 3520.3742 870.1533) 
(list 3520.3619 870.1636) 
(list 3520.3512 870.1739) 
(list 3520.3424 870.1842) 
(list 3520.3359 870.1944) 
(list 3520.3318 870.2047) 
(list 3520.3303 870.215) 
(list 3520.3314 870.2253) 
(list 3520.3351 870.2356) 
(list 3520.3413 870.2458) 
(list 3520.3499 870.2561) 
(list 3520.3606 870.2664) 
(list 3520.3731 870.2767) 
(list 3520.387 870.2869) 
(list 3520.4019 870.2972) 
(list 3520.4174 870.3075) 
(list 3520.4329 870.3178) 
(list 3520.4481 870.3281) 
(list 3520.4624 870.3383) 
(list 3520.4754 870.3486) 
(list 3520.4867 870.3589) 
(list 3520.496 870.3692) 
(list 3520.5029 870.3794) 
(list 3520.5073 870.3897) 
(list 3520.509 870.4) 
(list 3520.509 870.4)))
(apply 'command (append '("pline") coords '("c")))
(setq tap11 (ssadd (entlast) tap11))
(command "_mirror" (entlast) "" "3520,900" "3520,901" "No")
(setq tap11 (ssadd (entlast) tap11))
(setq coords (list 
(list 3521.122 870.03) 
(list 3520.509 870.03) 
(list 3520.509 870.0403) 
(list 3520.509 870.0506) 
(list 3520.509 870.0608) 
(list 3520.509 870.0711) 
(list 3520.509 870.0814) 
(list 3520.509 870.0917) 
(list 3520.509 870.1019) 
(list 3520.509 870.1122) 
(list 3520.509 870.1225) 
(list 3520.509 870.1328) 
(list 3520.509 870.1431) 
(list 3520.509 870.1533) 
(list 3520.509 870.1636) 
(list 3520.509 870.1739) 
(list 3520.509 870.1842) 
(list 3520.509 870.1944) 
(list 3520.509 870.2047) 
(list 3520.509 870.215) 
(list 3520.509 870.2253) 
(list 3520.509 870.2356) 
(list 3520.509 870.2458) 
(list 3520.509 870.2561) 
(list 3520.509 870.2664) 
(list 3520.509 870.2767) 
(list 3520.509 870.2869) 
(list 3520.509 870.2972) 
(list 3520.509 870.3075) 
(list 3520.509 870.3178) 
(list 3520.509 870.3281) 
(list 3520.509 870.3383) 
(list 3520.509 870.3486) 
(list 3520.509 870.3589) 
(list 3520.509 870.3692) 
(list 3520.509 870.3794) 
(list 3520.509 870.3897) 
(list 3520.509 870.4) 
(list 3521.122 870.4)))
(apply 'command (append '("pline") coords '("c")))
(setq tap11 (ssadd (entlast) tap11))
(command "_mirror" (entlast) "" "3520,900" "3520,901" "No")
(setq tap11 (ssadd (entlast) tap11))
(setq coords (list 
(list 3520 870.4) 
(list 3520.125 870.4) 
(list 3520.125 870.4103) 
(list 3520.125 870.4206) 
(list 3520.125 870.4308) 
(list 3520.125 870.4411) 
(list 3520.125 870.4514) 
(list 3520.125 870.4617) 
(list 3520.125 870.4719) 
(list 3520.125 870.4822) 
(list 3520.125 870.4925) 
(list 3520.125 870.5028) 
(list 3520.125 870.5131) 
(list 3520.125 870.5233) 
(list 3520.125 870.5336) 
(list 3520.125 870.5439) 
(list 3520.125 870.5542) 
(list 3520.125 870.5644) 
(list 3520.125 870.5747) 
(list 3520.125 870.585) 
(list 3520.125 870.5953) 
(list 3520.125 870.6056) 
(list 3520.125 870.6158) 
(list 3520.125 870.6261) 
(list 3520.125 870.6364) 
(list 3520.125 870.6467) 
(list 3520.125 870.6569) 
(list 3520.125 870.6672) 
(list 3520.125 870.6775) 
(list 3520.125 870.6878) 
(list 3520.125 870.6981) 
(list 3520.125 870.7083) 
(list 3520.125 870.7186) 
(list 3520.125 870.7289) 
(list 3520.125 870.7392) 
(list 3520.125 870.7494) 
(list 3520.125 870.7597) 
(list 3520.125 870.77) 
(list 3520 870.77)))
(apply 'command (append '("pline") coords '("c")))
(setq tap11 (ssadd (entlast) tap11))
(command "_mirror" (entlast) "" "3520,900" "3520,901" "No")
(setq tap11 (ssadd (entlast) tap11))
(setq coords (list 
(list 3520.5194 870.4) 
(list 3520.509 870.4) 
(list 3520.5079 870.4103) 
(list 3520.504 870.4206) 
(list 3520.4975 870.4308) 
(list 3520.4886 870.4411) 
(list 3520.4774 870.4514) 
(list 3520.4643 870.4617) 
(list 3520.4498 870.4719) 
(list 3520.4342 870.4822) 
(list 3520.418 870.4925) 
(list 3520.4017 870.5028) 
(list 3520.3859 870.5131) 
(list 3520.3709 870.5233) 
(list 3520.3573 870.5336) 
(list 3520.3455 870.5439) 
(list 3520.3358 870.5542) 
(list 3520.3286 870.5644) 
(list 3520.3241 870.5747) 
(list 3520.3224 870.585) 
(list 3520.3236 870.5953) 
(list 3520.3278 870.6056) 
(list 3520.3347 870.6158) 
(list 3520.3442 870.6261) 
(list 3520.356 870.6364) 
(list 3520.3698 870.6467) 
(list 3520.3851 870.6569) 
(list 3520.4016 870.6672) 
(list 3520.4186 870.6775) 
(list 3520.4357 870.6878) 
(list 3520.4524 870.6981) 
(list 3520.4682 870.7083) 
(list 3520.4825 870.7186) 
(list 3520.495 870.7289) 
(list 3520.5052 870.7392) 
(list 3520.5128 870.7494) 
(list 3520.5176 870.7597) 
(list 3520.5194 870.77) 
(list 3520.5194 870.77)))
(apply 'command (append '("pline") coords '("c")))
(setq tap11 (ssadd (entlast) tap11))
(command "_mirror" (entlast) "" "3520,900" "3520,901" "No")
(setq tap11 (ssadd (entlast) tap11))
(setq coords (list 
(list 3521.122 870.4) 
(list 3520.5194 870.4) 
(list 3520.5194 870.4103) 
(list 3520.5194 870.4206) 
(list 3520.5194 870.4308) 
(list 3520.5194 870.4411) 
(list 3520.5194 870.4514) 
(list 3520.5194 870.4617) 
(list 3520.5194 870.4719) 
(list 3520.5194 870.4822) 
(list 3520.5194 870.4925) 
(list 3520.5194 870.5028) 
(list 3520.5194 870.5131) 
(list 3520.5194 870.5233) 
(list 3520.5194 870.5336) 
(list 3520.5194 870.5439) 
(list 3520.5194 870.5542) 
(list 3520.5194 870.5644) 
(list 3520.5194 870.5747) 
(list 3520.5194 870.585) 
(list 3520.5194 870.5953) 
(list 3520.5194 870.6056) 
(list 3520.5194 870.6158) 
(list 3520.5194 870.6261) 
(list 3520.5194 870.6364) 
(list 3520.5194 870.6467) 
(list 3520.5194 870.6569) 
(list 3520.5194 870.6672) 
(list 3520.5194 870.6775) 
(list 3520.5194 870.6878) 
(list 3520.5194 870.6981) 
(list 3520.5194 870.7083) 
(list 3520.5194 870.7186) 
(list 3520.5194 870.7289) 
(list 3520.5194 870.7392) 
(list 3520.5194 870.7494) 
(list 3520.5194 870.7597) 
(list 3520.5194 870.77) 
(list 3521.122 870.77)))
(apply 'command (append '("pline") coords '("c")))
(setq tap11 (ssadd (entlast) tap11))
(command "_mirror" (entlast) "" "3520,900" "3520,901" "No")
(setq tap11 (ssadd (entlast) tap11))
(setq coords (list 
(list 3520 870.77) 
(list 3520.125 870.77) 
(list 3520.125 870.7803) 
(list 3520.125 870.7906) 
(list 3520.125 870.8008) 
(list 3520.125 870.8111) 
(list 3520.125 870.8214) 
(list 3520.125 870.8317) 
(list 3520.125 870.8419) 
(list 3520.125 870.8522) 
(list 3520.125 870.8625) 
(list 3520.125 870.8728) 
(list 3520.125 870.8831) 
(list 3520.125 870.8933) 
(list 3520.125 870.9036) 
(list 3520.125 870.9139) 
(list 3520.125 870.9242) 
(list 3520.125 870.9344) 
(list 3520.125 870.9447) 
(list 3520.125 870.955) 
(list 3520.125 870.9653) 
(list 3520.125 870.9756) 
(list 3520.125 870.9858) 
(list 3520.125 870.9961) 
(list 3520.125 871.0064) 
(list 3520.125 871.0167) 
(list 3520.125 871.0269) 
(list 3520.125 871.0372) 
(list 3520.125 871.0475) 
(list 3520.125 871.0578) 
(list 3520.125 871.0681) 
(list 3520.125 871.0783) 
(list 3520.125 871.0886) 
(list 3520.125 871.0989) 
(list 3520.125 871.1092) 
(list 3520.125 871.1194) 
(list 3520.125 871.1297) 
(list 3520.125 871.14) 
(list 3520 871.14)))
(apply 'command (append '("pline") coords '("c")))
(setq tap11 (ssadd (entlast) tap11))
(command "_mirror" (entlast) "" "3520,900" "3520,901" "No")
(setq tap11 (ssadd (entlast) tap11))
(setq coords (list 
(list 3520.5298 870.77) 
(list 3520.5194 870.77) 
(list 3520.5182 870.7803) 
(list 3520.5139 870.7906) 
(list 3520.5067 870.8008) 
(list 3520.4968 870.8111) 
(list 3520.4845 870.8214) 
(list 3520.4701 870.8317) 
(list 3520.4541 870.8419) 
(list 3520.437 870.8522) 
(list 3520.4192 870.8625) 
(list 3520.4014 870.8728) 
(list 3520.384 870.8831) 
(list 3520.3676 870.8933) 
(list 3520.3527 870.9036) 
(list 3520.3397 870.9139) 
(list 3520.3292 870.9242) 
(list 3520.3213 870.9344) 
(list 3520.3163 870.9447) 
(list 3520.3145 870.955) 
(list 3520.3159 870.9653) 
(list 3520.3205 870.9756) 
(list 3520.3281 870.9858) 
(list 3520.3385 870.9961) 
(list 3520.3514 871.0064) 
(list 3520.3665 871.0167) 
(list 3520.3833 871.0269) 
(list 3520.4013 871.0372) 
(list 3520.4199 871.0475) 
(list 3520.4386 871.0578) 
(list 3520.4568 871.0681) 
(list 3520.474 871.0783) 
(list 3520.4897 871.0886) 
(list 3520.5032 871.0989) 
(list 3520.5144 871.1092) 
(list 3520.5226 871.1194) 
(list 3520.5278 871.1297) 
(list 3520.5298 871.14) 
(list 3520.5298 871.14)))
(apply 'command (append '("pline") coords '("c")))
(setq tap11 (ssadd (entlast) tap11))
(command "_mirror" (entlast) "" "3520,900" "3520,901" "No")
(setq tap11 (ssadd (entlast) tap11))
(setq coords (list 
(list 3521.122 870.77) 
(list 3520.5298 870.77) 
(list 3520.5298 870.7803) 
(list 3520.5298 870.7906) 
(list 3520.5298 870.8008) 
(list 3520.5298 870.8111) 
(list 3520.5298 870.8214) 
(list 3520.5298 870.8317) 
(list 3520.5298 870.8419) 
(list 3520.5298 870.8522) 
(list 3520.5298 870.8625) 
(list 3520.5298 870.8728) 
(list 3520.5298 870.8831) 
(list 3520.5298 870.8933) 
(list 3520.5298 870.9036) 
(list 3520.5298 870.9139) 
(list 3520.5298 870.9242) 
(list 3520.5298 870.9344) 
(list 3520.5298 870.9447) 
(list 3520.5298 870.955) 
(list 3520.5298 870.9653) 
(list 3520.5298 870.9756) 
(list 3520.5298 870.9858) 
(list 3520.5298 870.9961) 
(list 3520.5298 871.0064) 
(list 3520.5298 871.0167) 
(list 3520.5298 871.0269) 
(list 3520.5298 871.0372) 
(list 3520.5298 871.0475) 
(list 3520.5298 871.0578) 
(list 3520.5298 871.0681) 
(list 3520.5298 871.0783) 
(list 3520.5298 871.0886) 
(list 3520.5298 871.0989) 
(list 3520.5298 871.1092) 
(list 3520.5298 871.1194) 
(list 3520.5298 871.1297) 
(list 3520.5298 871.14) 
(list 3521.122 871.14)))
(apply 'command (append '("pline") coords '("c")))
(setq tap11 (ssadd (entlast) tap11))
(command "_mirror" (entlast) "" "3520,900" "3520,901" "No")
(setq tap11 (ssadd (entlast) tap11))
(setq coords (list 
(list 3520 871.14) 
(list 3520.125 871.14) 
(list 3520.125 871.1503) 
(list 3520.125 871.1606) 
(list 3520.125 871.1708) 
(list 3520.125 871.1811) 
(list 3520.125 871.1914) 
(list 3520.125 871.2017) 
(list 3520.125 871.2119) 
(list 3520.125 871.2222) 
(list 3520.125 871.2325) 
(list 3520.125 871.2428) 
(list 3520.125 871.2531) 
(list 3520.125 871.2633) 
(list 3520.125 871.2736) 
(list 3520.125 871.2839) 
(list 3520.125 871.2942) 
(list 3520.125 871.3044) 
(list 3520.125 871.3147) 
(list 3520.125 871.325) 
(list 3520.125 871.3353) 
(list 3520.125 871.3456) 
(list 3520.125 871.3558) 
(list 3520.125 871.3661) 
(list 3520.125 871.3764) 
(list 3520.125 871.3867) 
(list 3520.125 871.3969) 
(list 3520.125 871.4072) 
(list 3520.125 871.4175) 
(list 3520.125 871.4278) 
(list 3520.125 871.4381) 
(list 3520.125 871.4483) 
(list 3520.125 871.4586) 
(list 3520.125 871.4689) 
(list 3520.125 871.4792) 
(list 3520.125 871.4894) 
(list 3520.125 871.4997) 
(list 3520.125 871.51) 
(list 3520 871.51)))
(apply 'command (append '("pline") coords '("c")))
(setq tap11 (ssadd (entlast) tap11))
(command "_mirror" (entlast) "" "3520,900" "3520,901" "No")
(setq tap11 (ssadd (entlast) tap11))
(setq coords (list 
(list 3520.5402 871.14) 
(list 3520.5298 871.14) 
(list 3520.5284 871.1503) 
(list 3520.5237 871.1606) 
(list 3520.5159 871.1708) 
(list 3520.5051 871.1811) 
(list 3520.4916 871.1914) 
(list 3520.476 871.2017) 
(list 3520.4585 871.2119) 
(list 3520.4399 871.2222) 
(list 3520.4205 871.2325) 
(list 3520.4011 871.2428) 
(list 3520.3821 871.2531) 
(list 3520.3643 871.2633) 
(list 3520.3481 871.2736) 
(list 3520.334 871.2839) 
(list 3520.3225 871.2942) 
(list 3520.314 871.3044) 
(list 3520.3086 871.3147) 
(list 3520.3067 871.325) 
(list 3520.3082 871.3353) 
(list 3520.3131 871.3456) 
(list 3520.3214 871.3558) 
(list 3520.3327 871.3661) 
(list 3520.3468 871.3764) 
(list 3520.3632 871.3867) 
(list 3520.3814 871.3969) 
(list 3520.4009 871.4072) 
(list 3520.4212 871.4175) 
(list 3520.4415 871.4278) 
(list 3520.4612 871.4381) 
(list 3520.4799 871.4483) 
(list 3520.4968 871.4586) 
(list 3520.5115 871.4689) 
(list 3520.5235 871.4792) 
(list 3520.5325 871.4894) 
(list 3520.5381 871.4997) 
(list 3520.5402 871.51) 
(list 3520.5402 871.51)))
(apply 'command (append '("pline") coords '("c")))
(setq tap11 (ssadd (entlast) tap11))
(command "_mirror" (entlast) "" "3520,900" "3520,901" "No")
(setq tap11 (ssadd (entlast) tap11))
(setq coords (list 
(list 3521.122 871.14) 
(list 3520.5402 871.14) 
(list 3520.5402 871.1503) 
(list 3520.5402 871.1606) 
(list 3520.5402 871.1708) 
(list 3520.5402 871.1811) 
(list 3520.5402 871.1914) 
(list 3520.5402 871.2017) 
(list 3520.5402 871.2119) 
(list 3520.5402 871.2222) 
(list 3520.5402 871.2325) 
(list 3520.5402 871.2428) 
(list 3520.5402 871.2531) 
(list 3520.5402 871.2633) 
(list 3520.5402 871.2736) 
(list 3520.5402 871.2839) 
(list 3520.5402 871.2942) 
(list 3520.5402 871.3044) 
(list 3520.5402 871.3147) 
(list 3520.5402 871.325) 
(list 3520.5402 871.3353) 
(list 3520.5402 871.3456) 
(list 3520.5402 871.3558) 
(list 3520.5402 871.3661) 
(list 3520.5402 871.3764) 
(list 3520.5402 871.3867) 
(list 3520.5402 871.3969) 
(list 3520.5402 871.4072) 
(list 3520.5402 871.4175) 
(list 3520.5402 871.4278) 
(list 3520.5402 871.4381) 
(list 3520.5402 871.4483) 
(list 3520.5402 871.4586) 
(list 3520.5402 871.4689) 
(list 3520.5402 871.4792) 
(list 3520.5402 871.4894) 
(list 3520.5402 871.4997) 
(list 3520.5402 871.51) 
(list 3521.122 871.51)))
(apply 'command (append '("pline") coords '("c")))
(setq tap11 (ssadd (entlast) tap11))
(command "_mirror" (entlast) "" "3520,900" "3520,901" "No")
(setq tap11 (ssadd (entlast) tap11))
(setq coords (list 
(list 3520 871.51) 
(list 3520.125 871.51) 
(list 3520.125 871.5203) 
(list 3520.125 871.5306) 
(list 3520.125 871.5408) 
(list 3520.125 871.5511) 
(list 3520.125 871.5614) 
(list 3520.125 871.5717) 
(list 3520.125 871.5819) 
(list 3520.125 871.5922) 
(list 3520.125 871.6025) 
(list 3520.125 871.6128) 
(list 3520.125 871.6231) 
(list 3520.125 871.6333) 
(list 3520.125 871.6436) 
(list 3520.125 871.6539) 
(list 3520.125 871.6642) 
(list 3520.125 871.6744) 
(list 3520.125 871.6847) 
(list 3520.125 871.695) 
(list 3520.125 871.7053) 
(list 3520.125 871.7156) 
(list 3520.125 871.7258) 
(list 3520.125 871.7361) 
(list 3520.125 871.7464) 
(list 3520.125 871.7567) 
(list 3520.125 871.7669) 
(list 3520.125 871.7772) 
(list 3520.125 871.7875) 
(list 3520.125 871.7978) 
(list 3520.125 871.8081) 
(list 3520.125 871.8183) 
(list 3520.125 871.8286) 
(list 3520.125 871.8389) 
(list 3520.125 871.8492) 
(list 3520.125 871.8594) 
(list 3520.125 871.8697) 
(list 3520.125 871.88) 
(list 3520 871.88)))
(apply 'command (append '("pline") coords '("c")))
(setq tap11 (ssadd (entlast) tap11))
(command "_mirror" (entlast) "" "3520,900" "3520,901" "No")
(setq tap11 (ssadd (entlast) tap11))
(setq coords (list 
(list 3520.5506 871.51) 
(list 3520.5402 871.51) 
(list 3520.5387 871.5203) 
(list 3520.5336 871.5306) 
(list 3520.5251 871.5408) 
(list 3520.5133 871.5511) 
(list 3520.4988 871.5614) 
(list 3520.4818 871.5717) 
(list 3520.4629 871.5819) 
(list 3520.4427 871.5922) 
(list 3520.4218 871.6025) 
(list 3520.4008 871.6128) 
(list 3520.3803 871.6231) 
(list 3520.361 871.6333) 
(list 3520.3435 871.6436) 
(list 3520.3283 871.6539) 
(list 3520.3159 871.6642) 
(list 3520.3066 871.6744) 
(list 3520.3009 871.6847) 
(list 3520.2988 871.695) 
(list 3520.3005 871.7053) 
(list 3520.3058 871.7156) 
(list 3520.3148 871.7258) 
(list 3520.327 871.7361) 
(list 3520.3422 871.7464) 
(list 3520.3599 871.7567) 
(list 3520.3796 871.7669) 
(list 3520.4006 871.7772) 
(list 3520.4224 871.7875) 
(list 3520.4443 871.7978) 
(list 3520.4656 871.8081) 
(list 3520.4857 871.8183) 
(list 3520.5039 871.8286) 
(list 3520.5198 871.8389) 
(list 3520.5327 871.8492) 
(list 3520.5423 871.8594) 
(list 3520.5484 871.8697) 
(list 3520.5506 871.88) 
(list 3520.5506 871.88)))
(apply 'command (append '("pline") coords '("c")))
(setq tap11 (ssadd (entlast) tap11))
(command "_mirror" (entlast) "" "3520,900" "3520,901" "No")
(setq tap11 (ssadd (entlast) tap11))
(setq coords (list 
(list 3521.122 871.51) 
(list 3520.5506 871.51) 
(list 3520.5506 871.5203) 
(list 3520.5506 871.5306) 
(list 3520.5506 871.5408) 
(list 3520.5506 871.5511) 
(list 3520.5506 871.5614) 
(list 3520.5506 871.5717) 
(list 3520.5506 871.5819) 
(list 3520.5506 871.5922) 
(list 3520.5506 871.6025) 
(list 3520.5506 871.6128) 
(list 3520.5506 871.6231) 
(list 3520.5506 871.6333) 
(list 3520.5506 871.6436) 
(list 3520.5506 871.6539) 
(list 3520.5506 871.6642) 
(list 3520.5506 871.6744) 
(list 3520.5506 871.6847) 
(list 3520.5506 871.695) 
(list 3520.5506 871.7053) 
(list 3520.5506 871.7156) 
(list 3520.5506 871.7258) 
(list 3520.5506 871.7361) 
(list 3520.5506 871.7464) 
(list 3520.5506 871.7567) 
(list 3520.5506 871.7669) 
(list 3520.5506 871.7772) 
(list 3520.5506 871.7875) 
(list 3520.5506 871.7978) 
(list 3520.5506 871.8081) 
(list 3520.5506 871.8183) 
(list 3520.5506 871.8286) 
(list 3520.5506 871.8389) 
(list 3520.5506 871.8492) 
(list 3520.5506 871.8594) 
(list 3520.5506 871.8697) 
(list 3520.5506 871.88) 
(list 3521.122 871.88)))
(apply 'command (append '("pline") coords '("c")))
(setq tap11 (ssadd (entlast) tap11))
(command "_mirror" (entlast) "" "3520,900" "3520,901" "No")
(setq tap11 (ssadd (entlast) tap11))
(setq coords (list 
(list 3520 871.88) 
(list 3520.125 871.88) 
(list 3520.125 871.8903) 
(list 3520.125 871.9006) 
(list 3520.125 871.9108) 
(list 3520.125 871.9211) 
(list 3520.125 871.9314) 
(list 3520.125 871.9417) 
(list 3520.125 871.9519) 
(list 3520.125 871.9622) 
(list 3520.125 871.9725) 
(list 3520.125 871.9828) 
(list 3520.125 871.9931) 
(list 3520.125 872.0033) 
(list 3520.125 872.0136) 
(list 3520.125 872.0239) 
(list 3520.125 872.0342) 
(list 3520.125 872.0444) 
(list 3520.125 872.0547) 
(list 3520.125 872.065) 
(list 3520.125 872.0753) 
(list 3520.125 872.0856) 
(list 3520.125 872.0958) 
(list 3520.125 872.1061) 
(list 3520.125 872.1164) 
(list 3520.125 872.1267) 
(list 3520.125 872.1369) 
(list 3520.125 872.1472) 
(list 3520.125 872.1575) 
(list 3520.125 872.1678) 
(list 3520.125 872.1781) 
(list 3520.125 872.1883) 
(list 3520.125 872.1986) 
(list 3520.125 872.2089) 
(list 3520.125 872.2192) 
(list 3520.125 872.2294) 
(list 3520.125 872.2397) 
(list 3520.125 872.25) 
(list 3520 872.25)))
(apply 'command (append '("pline") coords '("c")))
(setq tap11 (ssadd (entlast) tap11))
(command "_mirror" (entlast) "" "3520,900" "3520,901" "No")
(setq tap11 (ssadd (entlast) tap11))
(setq coords (list 
(list 3520.561 871.88) 
(list 3520.5506 871.88) 
(list 3520.5489 871.8903) 
(list 3520.5434 871.9006) 
(list 3520.5342 871.9108) 
(list 3520.5216 871.9211) 
(list 3520.5059 871.9314) 
(list 3520.4876 871.9417) 
(list 3520.4673 871.9519) 
(list 3520.4456 871.9622) 
(list 3520.423 871.9725) 
(list 3520.4004 871.9828) 
(list 3520.3784 871.9931) 
(list 3520.3577 872.0033) 
(list 3520.3389 872.0136) 
(list 3520.3226 872.0239) 
(list 3520.3092 872.0342) 
(list 3520.2993 872.0444) 
(list 3520.2932 872.0547) 
(list 3520.2909 872.065) 
(list 3520.2927 872.0753) 
(list 3520.2985 872.0856) 
(list 3520.3081 872.0958) 
(list 3520.3213 872.1061) 
(list 3520.3376 872.1164) 
(list 3520.3566 872.1267) 
(list 3520.3777 872.1369) 
(list 3520.4003 872.1472) 
(list 3520.4237 872.1575) 
(list 3520.4472 872.1678) 
(list 3520.47 872.1781) 
(list 3520.4915 872.1883) 
(list 3520.5111 872.1986) 
(list 3520.528 872.2089) 
(list 3520.5419 872.2192) 
(list 3520.5522 872.2294) 
(list 3520.5586 872.2397) 
(list 3520.561 872.25) 
(list 3520.561 872.25)))
(apply 'command (append '("pline") coords '("c")))
(setq tap11 (ssadd (entlast) tap11))
(command "_mirror" (entlast) "" "3520,900" "3520,901" "No")
(setq tap11 (ssadd (entlast) tap11))
(setq coords (list 
(list 3521.122 871.88) 
(list 3520.561 871.88) 
(list 3520.561 871.8903) 
(list 3520.561 871.9006) 
(list 3520.561 871.9108) 
(list 3520.561 871.9211) 
(list 3520.561 871.9314) 
(list 3520.561 871.9417) 
(list 3520.561 871.9519) 
(list 3520.561 871.9622) 
(list 3520.561 871.9725) 
(list 3520.561 871.9828) 
(list 3520.561 871.9931) 
(list 3520.561 872.0033) 
(list 3520.561 872.0136) 
(list 3520.561 872.0239) 
(list 3520.561 872.0342) 
(list 3520.561 872.0444) 
(list 3520.561 872.0547) 
(list 3520.561 872.065) 
(list 3520.561 872.0753) 
(list 3520.561 872.0856) 
(list 3520.561 872.0958) 
(list 3520.561 872.1061) 
(list 3520.561 872.1164) 
(list 3520.561 872.1267) 
(list 3520.561 872.1369) 
(list 3520.561 872.1472) 
(list 3520.561 872.1575) 
(list 3520.561 872.1678) 
(list 3520.561 872.1781) 
(list 3520.561 872.1883) 
(list 3520.561 872.1986) 
(list 3520.561 872.2089) 
(list 3520.561 872.2192) 
(list 3520.561 872.2294) 
(list 3520.561 872.2397) 
(list 3520.561 872.25) 
(list 3521.122 872.25)))
(apply 'command (append '("pline") coords '("c")))
(setq tap11 (ssadd (entlast) tap11))
(command "_mirror" (entlast) "" "3520,900" "3520,901" "No")
(setq tap11 (ssadd (entlast) tap11))
(command "_block" "blktap11" "3520,900" tap11 "")
(command "_insert" "blktap11" "3520,900" "1" "1" "0")
(command "_insert" "blktap11" "3520,900" "1" "1" "180")
(setq uc11 nil)
(setq uc11 (ssadd))
(setq coords (list 
(list 0 -0.185) 
(list 0.125 -0.185) 
(list 0.125 -0.17472) 
(list 0.125 -0.16444) 
(list 0.125 -0.15417) 
(list 0.125 -0.14389) 
(list 0.125 -0.13361) 
(list 0.125 -0.12333) 
(list 0.125 -0.11306) 
(list 0.125 -0.10278) 
(list 0.125 -0.0925) 
(list 0.125 -0.082222) 
(list 0.125 -0.071944) 
(list 0.125 -0.061667) 
(list 0.125 -0.051389) 
(list 0.125 -0.041111) 
(list 0.125 -0.030833) 
(list 0.125 -0.020556) 
(list 0.125 -0.010278) 
(list 0.125 0) 
(list 0.125 0.010278) 
(list 0.125 0.020556) 
(list 0.125 0.030833) 
(list 0.125 0.041111) 
(list 0.125 0.051389) 
(list 0.125 0.061667) 
(list 0.125 0.071944) 
(list 0.125 0.082222) 
(list 0.125 0.0925) 
(list 0.125 0.10278) 
(list 0.125 0.11306) 
(list 0.125 0.12333) 
(list 0.125 0.13361) 
(list 0.125 0.14389) 
(list 0.125 0.15417) 
(list 0.125 0.16444) 
(list 0.125 0.17472) 
(list 0.125 0.185) 
(list 0 0.185)))
(apply 'command (append '("pline") coords '("c")))
(setq uc11 (ssadd (entlast) uc11))
(setq coords (list 
(list 1.122 -0.185) 
(list 0.561 -0.185) 
(list 0.55892 -0.17472) 
(list 0.55274 -0.16444) 
(list 0.54265 -0.15417) 
(list 0.52895 -0.14389) 
(list 0.51206 -0.13361) 
(list 0.4925 -0.12333) 
(list 0.47086 -0.11306) 
(list 0.44779 -0.10278) 
(list 0.424 -0.0925) 
(list 0.40021 -0.082222) 
(list 0.37714 -0.071944) 
(list 0.3555 -0.061667) 
(list 0.33594 -0.051389) 
(list 0.31905 -0.041111) 
(list 0.30535 -0.030833) 
(list 0.29526 -0.020556) 
(list 0.28908 -0.010278) 
(list 0.287 0) 
(list 0.28908 0.010278) 
(list 0.29526 0.020556) 
(list 0.30535 0.030833) 
(list 0.31905 0.041111) 
(list 0.33594 0.051389) 
(list 0.3555 0.061667) 
(list 0.37714 0.071944) 
(list 0.40021 0.082222) 
(list 0.424 0.0925) 
(list 0.44779 0.10278) 
(list 0.47086 0.11306) 
(list 0.4925 0.12333) 
(list 0.51206 0.13361) 
(list 0.52895 0.14389) 
(list 0.54265 0.15417) 
(list 0.55274 0.16444) 
(list 0.55892 0.17472) 
(list 0.561 0.185) 
(list 1.122 0.185)))
(apply 'command (append '("pline") coords '("c")))
(setq uc11 (ssadd (entlast) uc11))
(command "_block" "blkuc11" "0,0.185" uc11 "")
(command "_insert" "blkuc11" "3520,872.62" "1" "1" "0")
(command "_insert" "blkuc11" "3520,872.25" "1" "1" "180")
(command "_insert" "blkuc11" "3520,872.99" "1" "1" "0")
(command "_insert" "blkuc11" "3520,872.62" "1" "1" "180")
(command "_insert" "blkuc11" "3520,873.36" "1" "1" "0")
(command "_insert" "blkuc11" "3520,872.99" "1" "1" "180")
(command "_insert" "blkuc11" "3520,873.73" "1" "1" "0")
(command "_insert" "blkuc11" "3520,873.36" "1" "1" "180")
(command "_insert" "blkuc11" "3520,874.1" "1" "1" "0")
(command "_insert" "blkuc11" "3520,873.73" "1" "1" "180")
(command "_insert" "blkuc11" "3520,874.47" "1" "1" "0")
(command "_insert" "blkuc11" "3520,874.1" "1" "1" "180")
(command "_insert" "blkuc11" "3520,874.84" "1" "1" "0")
(command "_insert" "blkuc11" "3520,874.47" "1" "1" "180")
(command "_insert" "blkuc11" "3520,875.21" "1" "1" "0")
(command "_insert" "blkuc11" "3520,874.84" "1" "1" "180")
(command "_insert" "blkuc11" "3520,875.58" "1" "1" "0")
(command "_insert" "blkuc11" "3520,875.21" "1" "1" "180")
(command "_insert" "blkuc11" "3520,875.95" "1" "1" "0")
(command "_insert" "blkuc11" "3520,875.58" "1" "1" "180")
(command "_insert" "blkuc11" "3520,876.32" "1" "1" "0")
(command "_insert" "blkuc11" "3520,875.95" "1" "1" "180")
(command "_insert" "blkuc11" "3520,876.69" "1" "1" "0")
(command "_insert" "blkuc11" "3520,876.32" "1" "1" "180")
(command "_insert" "blkuc11" "3520,877.06" "1" "1" "0")
(command "_insert" "blkuc11" "3520,876.69" "1" "1" "180")
(command "_insert" "blkuc11" "3520,877.43" "1" "1" "0")
(command "_insert" "blkuc11" "3520,877.06" "1" "1" "180")
(command "_insert" "blkuc11" "3520,877.8" "1" "1" "0")
(command "_insert" "blkuc11" "3520,877.43" "1" "1" "180")
(command "_insert" "blkuc11" "3520,878.17" "1" "1" "0")
(command "_insert" "blkuc11" "3520,877.8" "1" "1" "180")
(command "_insert" "blkuc11" "3520,878.54" "1" "1" "0")
(command "_insert" "blkuc11" "3520,878.17" "1" "1" "180")
(command "_insert" "blkuc11" "3520,878.91" "1" "1" "0")
(command "_insert" "blkuc11" "3520,878.54" "1" "1" "180")
(command "_insert" "blkuc11" "3520,879.28" "1" "1" "0")
(command "_insert" "blkuc11" "3520,878.91" "1" "1" "180")
(command "_insert" "blkuc11" "3520,879.65" "1" "1" "0")
(command "_insert" "blkuc11" "3520,879.28" "1" "1" "180")
(command "_insert" "blkuc11" "3520,880.02" "1" "1" "0")
(command "_insert" "blkuc11" "3520,879.65" "1" "1" "180")
(command "_insert" "blkuc11" "3520,880.39" "1" "1" "0")
(command "_insert" "blkuc11" "3520,880.02" "1" "1" "180")
(command "_insert" "blkuc11" "3520,880.76" "1" "1" "0")
(command "_insert" "blkuc11" "3520,880.39" "1" "1" "180")
(command "_insert" "blkuc11" "3520,881.13" "1" "1" "0")
(command "_insert" "blkuc11" "3520,880.76" "1" "1" "180")
(command "_insert" "blkuc11" "3520,881.5" "1" "1" "0")
(command "_insert" "blkuc11" "3520,881.13" "1" "1" "180")
(command "_insert" "blkuc11" "3520,881.87" "1" "1" "0")
(command "_insert" "blkuc11" "3520,881.5" "1" "1" "180")
(command "_insert" "blkuc11" "3520,882.24" "1" "1" "0")
(command "_insert" "blkuc11" "3520,881.87" "1" "1" "180")
(command "_insert" "blkuc11" "3520,882.61" "1" "1" "0")
(command "_insert" "blkuc11" "3520,882.24" "1" "1" "180")
(command "_insert" "blkuc11" "3520,882.98" "1" "1" "0")
(command "_insert" "blkuc11" "3520,882.61" "1" "1" "180")
(command "_insert" "blkuc11" "3520,883.35" "1" "1" "0")
(command "_insert" "blkuc11" "3520,882.98" "1" "1" "180")
(command "_insert" "blkuc11" "3520,883.72" "1" "1" "0")
(command "_insert" "blkuc11" "3520,883.35" "1" "1" "180")
(command "_insert" "blkuc11" "3520,884.09" "1" "1" "0")
(command "_insert" "blkuc11" "3520,883.72" "1" "1" "180")
(command "_insert" "blkuc11" "3520,884.46" "1" "1" "0")
(command "_insert" "blkuc11" "3520,884.09" "1" "1" "180")
(command "_insert" "blkuc11" "3520,884.83" "1" "1" "0")
(command "_insert" "blkuc11" "3520,884.46" "1" "1" "180")
(command "_insert" "blkuc11" "3520,885.2" "1" "1" "0")
(command "_insert" "blkuc11" "3520,884.83" "1" "1" "180")
(command "_insert" "blkuc11" "3520,885.57" "1" "1" "0")
(command "_insert" "blkuc11" "3520,885.2" "1" "1" "180")
(command "_insert" "blkuc11" "3520,885.94" "1" "1" "0")
(command "_insert" "blkuc11" "3520,885.57" "1" "1" "180")
(command "_insert" "blkuc11" "3520,886.31" "1" "1" "0")
(command "_insert" "blkuc11" "3520,885.94" "1" "1" "180")
(command "_insert" "blkuc11" "3520,886.68" "1" "1" "0")
(command "_insert" "blkuc11" "3520,886.31" "1" "1" "180")
(command "_insert" "blkuc11" "3520,887.05" "1" "1" "0")
(command "_insert" "blkuc11" "3520,886.68" "1" "1" "180")
(command "_insert" "blkuc11" "3520,887.42" "1" "1" "0")
(command "_insert" "blkuc11" "3520,887.05" "1" "1" "180")
(command "_insert" "blkuc11" "3520,887.79" "1" "1" "0")
(command "_insert" "blkuc11" "3520,887.42" "1" "1" "180")
(command "_insert" "blkuc11" "3520,888.16" "1" "1" "0")
(command "_insert" "blkuc11" "3520,887.79" "1" "1" "180")
(command "_insert" "blkuc11" "3520,888.53" "1" "1" "0")
(command "_insert" "blkuc11" "3520,888.16" "1" "1" "180")
(command "_insert" "blkuc11" "3520,888.9" "1" "1" "0")
(command "_insert" "blkuc11" "3520,888.53" "1" "1" "180")
(command "_insert" "blkuc11" "3520,889.27" "1" "1" "0")
(command "_insert" "blkuc11" "3520,888.9" "1" "1" "180")
(command "_insert" "blkuc11" "3520,889.64" "1" "1" "0")
(command "_insert" "blkuc11" "3520,889.27" "1" "1" "180")
(command "_insert" "blkuc11" "3520,890.01" "1" "1" "0")
(command "_insert" "blkuc11" "3520,889.64" "1" "1" "180")
(command "_insert" "blkuc11" "3520,890.38" "1" "1" "0")
(command "_insert" "blkuc11" "3520,890.01" "1" "1" "180")
(command "_insert" "blkuc11" "3520,890.75" "1" "1" "0")
(command "_insert" "blkuc11" "3520,890.38" "1" "1" "180")
(command "_insert" "blkuc11" "3520,891.12" "1" "1" "0")
(command "_insert" "blkuc11" "3520,890.75" "1" "1" "180")
(command "_insert" "blkuc11" "3520,891.49" "1" "1" "0")
(command "_insert" "blkuc11" "3520,891.12" "1" "1" "180")
(command "_insert" "blkuc11" "3520,891.86" "1" "1" "0")
(command "_insert" "blkuc11" "3520,891.49" "1" "1" "180")
(command "_insert" "blkuc11" "3520,892.23" "1" "1" "0")
(command "_insert" "blkuc11" "3520,891.86" "1" "1" "180")
(command "_insert" "blkuc11" "3520,892.6" "1" "1" "0")
(command "_insert" "blkuc11" "3520,892.23" "1" "1" "180")
(command "_insert" "blkuc11" "3520,892.97" "1" "1" "0")
(command "_insert" "blkuc11" "3520,892.6" "1" "1" "180")
(command "_insert" "blkuc11" "3520,893.34" "1" "1" "0")
(command "_insert" "blkuc11" "3520,892.97" "1" "1" "180")
(command "_insert" "blkuc11" "3520,893.71" "1" "1" "0")
(command "_insert" "blkuc11" "3520,893.34" "1" "1" "180")
(command "_insert" "blkuc11" "3520,894.08" "1" "1" "0")
(command "_insert" "blkuc11" "3520,893.71" "1" "1" "180")
(command "_insert" "blkuc11" "3520,894.45" "1" "1" "0")
(command "_insert" "blkuc11" "3520,894.08" "1" "1" "180")
(command "_insert" "blkuc11" "3520,894.82" "1" "1" "0")
(command "_insert" "blkuc11" "3520,894.45" "1" "1" "180")
(command "_insert" "blkuc11" "3520,895.19" "1" "1" "0")
(command "_insert" "blkuc11" "3520,894.82" "1" "1" "180")
(command "_insert" "blkuc11" "3520,895.56" "1" "1" "0")
(command "_insert" "blkuc11" "3520,895.19" "1" "1" "180")
(command "_insert" "blkuc11" "3520,895.93" "1" "1" "0")
(command "_insert" "blkuc11" "3520,895.56" "1" "1" "180")
(command "_insert" "blkuc11" "3520,896.3" "1" "1" "0")
(command "_insert" "blkuc11" "3520,895.93" "1" "1" "180")
(command "_insert" "blkuc11" "3520,896.67" "1" "1" "0")
(command "_insert" "blkuc11" "3520,896.3" "1" "1" "180")
(command "_insert" "blkuc11" "3520,897.04" "1" "1" "0")
(command "_insert" "blkuc11" "3520,896.67" "1" "1" "180")
(command "_insert" "blkuc11" "3520,897.41" "1" "1" "0")
(command "_insert" "blkuc11" "3520,897.04" "1" "1" "180")
(command "_insert" "blkuc11" "3520,897.78" "1" "1" "0")
(command "_insert" "blkuc11" "3520,897.41" "1" "1" "180")
(command "_insert" "blkuc11" "3520,898.15" "1" "1" "0")
(command "_insert" "blkuc11" "3520,897.78" "1" "1" "180")
(command "_insert" "blkuc11" "3520,898.52" "1" "1" "0")
(command "_insert" "blkuc11" "3520,898.15" "1" "1" "180")
(command "_insert" "blkuc11" "3520,898.89" "1" "1" "0")
(command "_insert" "blkuc11" "3520,898.52" "1" "1" "180")
(command "_insert" "blkuc11" "3520,899.26" "1" "1" "0")
(command "_insert" "blkuc11" "3520,898.89" "1" "1" "180")
(command "_insert" "blkuc11" "3520,899.63" "1" "1" "0")
(command "_insert" "blkuc11" "3520,899.26" "1" "1" "180")
(command "_insert" "blkuc11" "3520,900" "1" "1" "0")
(command "_insert" "blkuc11" "3520,899.63" "1" "1" "180")
(command "_insert" "blkuc11" "3520,900.37" "1" "1" "0")
(command "_insert" "blkuc11" "3520,900" "1" "1" "180")
(command "_insert" "blkuc11" "3520,900.74" "1" "1" "0")
(command "_insert" "blkuc11" "3520,900.37" "1" "1" "180")
(command "_insert" "blkuc11" "3520,901.11" "1" "1" "0")
(command "_insert" "blkuc11" "3520,900.74" "1" "1" "180")
(command "_insert" "blkuc11" "3520,901.48" "1" "1" "0")
(command "_insert" "blkuc11" "3520,901.11" "1" "1" "180")
(command "_insert" "blkuc11" "3520,901.85" "1" "1" "0")
(command "_insert" "blkuc11" "3520,901.48" "1" "1" "180")
(command "_insert" "blkuc11" "3520,902.22" "1" "1" "0")
(command "_insert" "blkuc11" "3520,901.85" "1" "1" "180")
(command "_insert" "blkuc11" "3520,902.59" "1" "1" "0")
(command "_insert" "blkuc11" "3520,902.22" "1" "1" "180")
(command "_insert" "blkuc11" "3520,902.96" "1" "1" "0")
(command "_insert" "blkuc11" "3520,902.59" "1" "1" "180")
(command "_insert" "blkuc11" "3520,903.33" "1" "1" "0")
(command "_insert" "blkuc11" "3520,902.96" "1" "1" "180")
(command "_insert" "blkuc11" "3520,903.7" "1" "1" "0")
(command "_insert" "blkuc11" "3520,903.33" "1" "1" "180")
(command "_insert" "blkuc11" "3520,904.07" "1" "1" "0")
(command "_insert" "blkuc11" "3520,903.7" "1" "1" "180")
(command "_insert" "blkuc11" "3520,904.44" "1" "1" "0")
(command "_insert" "blkuc11" "3520,904.07" "1" "1" "180")
(command "_insert" "blkuc11" "3520,904.81" "1" "1" "0")
(command "_insert" "blkuc11" "3520,904.44" "1" "1" "180")
(command "_insert" "blkuc11" "3520,905.18" "1" "1" "0")
(command "_insert" "blkuc11" "3520,904.81" "1" "1" "180")
(command "_insert" "blkuc11" "3520,905.55" "1" "1" "0")
(command "_insert" "blkuc11" "3520,905.18" "1" "1" "180")
(command "_insert" "blkuc11" "3520,905.92" "1" "1" "0")
(command "_insert" "blkuc11" "3520,905.55" "1" "1" "180")
(command "_insert" "blkuc11" "3520,906.29" "1" "1" "0")
(command "_insert" "blkuc11" "3520,905.92" "1" "1" "180")
(command "_insert" "blkuc11" "3520,906.66" "1" "1" "0")
(command "_insert" "blkuc11" "3520,906.29" "1" "1" "180")
(command "_insert" "blkuc11" "3520,907.03" "1" "1" "0")
(command "_insert" "blkuc11" "3520,906.66" "1" "1" "180")
(command "_insert" "blkuc11" "3520,907.4" "1" "1" "0")
(command "_insert" "blkuc11" "3520,907.03" "1" "1" "180")
(command "_insert" "blkuc11" "3520,907.77" "1" "1" "0")
(command "_insert" "blkuc11" "3520,907.4" "1" "1" "180")
(command "_insert" "blkuc11" "3520,908.14" "1" "1" "0")
(command "_insert" "blkuc11" "3520,907.77" "1" "1" "180")
(command "_insert" "blkuc11" "3520,908.51" "1" "1" "0")
(command "_insert" "blkuc11" "3520,908.14" "1" "1" "180")
(command "_insert" "blkuc11" "3520,908.88" "1" "1" "0")
(command "_insert" "blkuc11" "3520,908.51" "1" "1" "180")
(command "_insert" "blkuc11" "3520,909.25" "1" "1" "0")
(command "_insert" "blkuc11" "3520,908.88" "1" "1" "180")
(command "_insert" "blkuc11" "3520,909.62" "1" "1" "0")
(command "_insert" "blkuc11" "3520,909.25" "1" "1" "180")
(command "_insert" "blkuc11" "3520,909.99" "1" "1" "0")
(command "_insert" "blkuc11" "3520,909.62" "1" "1" "180")
(command "_insert" "blkuc11" "3520,910.36" "1" "1" "0")
(command "_insert" "blkuc11" "3520,909.99" "1" "1" "180")
(command "_insert" "blkuc11" "3520,910.73" "1" "1" "0")
(command "_insert" "blkuc11" "3520,910.36" "1" "1" "180")
(command "_insert" "blkuc11" "3520,911.1" "1" "1" "0")
(command "_insert" "blkuc11" "3520,910.73" "1" "1" "180")
(command "_insert" "blkuc11" "3520,911.47" "1" "1" "0")
(command "_insert" "blkuc11" "3520,911.1" "1" "1" "180")
(command "_insert" "blkuc11" "3520,911.84" "1" "1" "0")
(command "_insert" "blkuc11" "3520,911.47" "1" "1" "180")
(command "_insert" "blkuc11" "3520,912.21" "1" "1" "0")
(command "_insert" "blkuc11" "3520,911.84" "1" "1" "180")
(command "_insert" "blkuc11" "3520,912.58" "1" "1" "0")
(command "_insert" "blkuc11" "3520,912.21" "1" "1" "180")
(command "_insert" "blkuc11" "3520,912.95" "1" "1" "0")
(command "_insert" "blkuc11" "3520,912.58" "1" "1" "180")
(command "_insert" "blkuc11" "3520,913.32" "1" "1" "0")
(command "_insert" "blkuc11" "3520,912.95" "1" "1" "180")
(command "_insert" "blkuc11" "3520,913.69" "1" "1" "0")
(command "_insert" "blkuc11" "3520,913.32" "1" "1" "180")
(command "_insert" "blkuc11" "3520,914.06" "1" "1" "0")
(command "_insert" "blkuc11" "3520,913.69" "1" "1" "180")
(command "_insert" "blkuc11" "3520,914.43" "1" "1" "0")
(command "_insert" "blkuc11" "3520,914.06" "1" "1" "180")
(command "_insert" "blkuc11" "3520,914.8" "1" "1" "0")
(command "_insert" "blkuc11" "3520,914.43" "1" "1" "180")
(command "_insert" "blkuc11" "3520,915.17" "1" "1" "0")
(command "_insert" "blkuc11" "3520,914.8" "1" "1" "180")
(command "_insert" "blkuc11" "3520,915.54" "1" "1" "0")
(command "_insert" "blkuc11" "3520,915.17" "1" "1" "180")
(command "_insert" "blkuc11" "3520,915.91" "1" "1" "0")
(command "_insert" "blkuc11" "3520,915.54" "1" "1" "180")
(command "_insert" "blkuc11" "3520,916.28" "1" "1" "0")
(command "_insert" "blkuc11" "3520,915.91" "1" "1" "180")
(command "_insert" "blkuc11" "3520,916.65" "1" "1" "0")
(command "_insert" "blkuc11" "3520,916.28" "1" "1" "180")
(command "_insert" "blkuc11" "3520,917.02" "1" "1" "0")
(command "_insert" "blkuc11" "3520,916.65" "1" "1" "180")
(command "_insert" "blkuc11" "3520,917.39" "1" "1" "0")
(command "_insert" "blkuc11" "3520,917.02" "1" "1" "180")
(command "_insert" "blkuc11" "3520,917.76" "1" "1" "0")
(command "_insert" "blkuc11" "3520,917.39" "1" "1" "180")
(command "_insert" "blkuc11" "3520,918.13" "1" "1" "0")
(command "_insert" "blkuc11" "3520,917.76" "1" "1" "180")
(command "_insert" "blkuc11" "3520,918.5" "1" "1" "0")
(command "_insert" "blkuc11" "3520,918.13" "1" "1" "180")
(command "_insert" "blkuc11" "3520,918.87" "1" "1" "0")
(command "_insert" "blkuc11" "3520,918.5" "1" "1" "180")
(command "_insert" "blkuc11" "3520,919.24" "1" "1" "0")
(command "_insert" "blkuc11" "3520,918.87" "1" "1" "180")
(command "_insert" "blkuc11" "3520,919.61" "1" "1" "0")
(command "_insert" "blkuc11" "3520,919.24" "1" "1" "180")
(command "_insert" "blkuc11" "3520,919.98" "1" "1" "0")
(command "_insert" "blkuc11" "3520,919.61" "1" "1" "180")
(command "_insert" "blkuc11" "3520,920.35" "1" "1" "0")
(command "_insert" "blkuc11" "3520,919.98" "1" "1" "180")
(command "_insert" "blkuc11" "3520,920.72" "1" "1" "0")
(command "_insert" "blkuc11" "3520,920.35" "1" "1" "180")
(command "_insert" "blkuc11" "3520,921.09" "1" "1" "0")
(command "_insert" "blkuc11" "3520,920.72" "1" "1" "180")
(command "_insert" "blkuc11" "3520,921.46" "1" "1" "0")
(command "_insert" "blkuc11" "3520,921.09" "1" "1" "180")
(command "_insert" "blkuc11" "3520,921.83" "1" "1" "0")
(command "_insert" "blkuc11" "3520,921.46" "1" "1" "180")
(command "_insert" "blkuc11" "3520,922.2" "1" "1" "0")
(command "_insert" "blkuc11" "3520,921.83" "1" "1" "180")
(command "_insert" "blkuc11" "3520,922.57" "1" "1" "0")
(command "_insert" "blkuc11" "3520,922.2" "1" "1" "180")
(command "_insert" "blkuc11" "3520,922.94" "1" "1" "0")
(command "_insert" "blkuc11" "3520,922.57" "1" "1" "180")
(command "_insert" "blkuc11" "3520,923.31" "1" "1" "0")
(command "_insert" "blkuc11" "3520,922.94" "1" "1" "180")
(command "_insert" "blkuc11" "3520,923.68" "1" "1" "0")
(command "_insert" "blkuc11" "3520,923.31" "1" "1" "180")
(command "_insert" "blkuc11" "3520,924.05" "1" "1" "0")
(command "_insert" "blkuc11" "3520,923.68" "1" "1" "180")
(command "_insert" "blkuc11" "3520,924.42" "1" "1" "0")
(command "_insert" "blkuc11" "3520,924.05" "1" "1" "180")
(command "_insert" "blkuc11" "3520,924.79" "1" "1" "0")
(command "_insert" "blkuc11" "3520,924.42" "1" "1" "180")
(command "_insert" "blkuc11" "3520,925.16" "1" "1" "0")
(command "_insert" "blkuc11" "3520,924.79" "1" "1" "180")
(command "_insert" "blkuc11" "3520,925.53" "1" "1" "0")
(command "_insert" "blkuc11" "3520,925.16" "1" "1" "180")
(command "_insert" "blkuc11" "3520,925.9" "1" "1" "0")
(command "_insert" "blkuc11" "3520,925.53" "1" "1" "180")
(command "_insert" "blkuc11" "3520,926.27" "1" "1" "0")
(command "_insert" "blkuc11" "3520,925.9" "1" "1" "180")
(command "_insert" "blkuc11" "3520,926.64" "1" "1" "0")
(command "_insert" "blkuc11" "3520,926.27" "1" "1" "180")
(command "_insert" "blkuc11" "3520,927.01" "1" "1" "0")
(command "_insert" "blkuc11" "3520,926.64" "1" "1" "180")
(command "_insert" "blkuc11" "3520,927.38" "1" "1" "0")
(command "_insert" "blkuc11" "3520,927.01" "1" "1" "180")
(command "_insert" "blkuc11" "3520,927.75" "1" "1" "0")
(command "_insert" "blkuc11" "3520,927.38" "1" "1" "180")
(command "_layer" "set" "phccover" "")
(command "_rectangle" "3518.878,933.3" "3521.122,866.7")
(command "_layer" "set" "nitride" "")
(setq phc11 currobj)
(command "_layer" "set" "cover" "")
(command "_rectangle" "3518.878,836.7" "3521.122,963.3")
(command "_layer" "set" "nitride" "")
(command "_layer" "set" "text" "")
(command "_circle" "3517.928,846.7" "0.075")
(command "_circle" "3517.553,846.7" "0.15")
(command "_circle" "3517.178,846.7" "0.075")
(command "_circle" "3516.803,846.7" "0.15")
(command "_circle" "3517.928,848.7" "0.075")
(command "_circle" "3517.553,848.7" "0.075")
(command "_circle" "3517.178,848.7" "0.15")
(command "_circle" "3516.803,848.7" "0.15")
(command "_circle" "3517.928,850.7" "0.075")
(command "_circle" "3517.553,850.7" "0.15")
(command "_circle" "3517.178,850.7" "0.15")
(command "_circle" "3516.803,850.7" "0.15")
(command "_circle" "3517.928,852.7" "0.075")
(command "_circle" "3517.553,852.7" "0.075")
(command "_circle" "3517.178,852.7" "0.075")
(command "_circle" "3516.803,852.7" "0.075")
(command "_circle" "3516.428,852.7" "0.15")
(command "_circle" "3517.928,854.7" "0.075")
(command "_circle" "3517.553,854.7" "0.15")
(command "_circle" "3517.178,854.7" "0.075")
(command "_circle" "3516.803,854.7" "0.075")
(command "_circle" "3516.428,854.7" "0.15")
(command "_circle" "3517.928,856.7" "0.075")
(command "_circle" "3517.553,856.7" "0.075")
(command "_circle" "3517.178,856.7" "0.15")
(command "_circle" "3516.803,856.7" "0.075")
(command "_circle" "3516.428,856.7" "0.15")
(command "_circle" "3517.928,858.7" "0.075")
(command "_circle" "3517.553,858.7" "0.15")
(command "_circle" "3517.178,858.7" "0.15")
(command "_circle" "3516.803,858.7" "0.075")
(command "_circle" "3516.428,858.7" "0.15")
(command "_circle" "3517.928,860.7" "0.075")
(command "_circle" "3517.553,860.7" "0.075")
(command "_circle" "3517.178,860.7" "0.075")
(command "_circle" "3516.803,860.7" "0.15")
(command "_circle" "3516.428,860.7" "0.15")
(command "_circle" "3517.928,862.7" "0.075")
(command "_circle" "3517.553,862.7" "0.15")
(command "_circle" "3517.178,862.7" "0.075")
(command "_circle" "3516.803,862.7" "0.15")
(command "_circle" "3516.428,862.7" "0.15")
(command "_circle" "3517.928,864.7" "0.075")
(command "_circle" "3517.553,864.7" "0.075")
(command "_circle" "3517.178,864.7" "0.15")
(command "_circle" "3516.803,864.7" "0.15")
(command "_circle" "3516.428,864.7" "0.15")
(command "_circle" "3517.928,866.7" "0.075")
(command "_circle" "3517.553,866.7" "0.15")
(command "_circle" "3517.178,866.7" "0.15")
(command "_circle" "3516.803,866.7" "0.15")
(command "_circle" "3516.428,866.7" "0.15")
(command "_circle" "3517.928,868.7" "0.075")
(command "_circle" "3517.553,868.7" "0.075")
(command "_circle" "3517.178,868.7" "0.075")
(command "_circle" "3516.803,868.7" "0.075")
(command "_circle" "3516.428,868.7" "0.075")
(command "_circle" "3516.053,868.7" "0.15")
(command "_circle" "3517.928,870.7" "0.075")
(command "_circle" "3517.553,870.7" "0.15")
(command "_circle" "3517.178,870.7" "0.075")
(command "_circle" "3516.803,870.7" "0.075")
(command "_circle" "3516.428,870.7" "0.075")
(command "_circle" "3516.053,870.7" "0.15")
(command "_circle" "3517.928,872.7" "0.075")
(command "_circle" "3517.553,872.7" "0.075")
(command "_circle" "3517.178,872.7" "0.15")
(command "_circle" "3516.803,872.7" "0.075")
(command "_circle" "3516.428,872.7" "0.075")
(command "_circle" "3516.053,872.7" "0.15")
(command "_circle" "3517.928,874.7" "0.075")
(command "_circle" "3517.553,874.7" "0.15")
(command "_circle" "3517.178,874.7" "0.15")
(command "_circle" "3516.803,874.7" "0.075")
(command "_circle" "3516.428,874.7" "0.075")
(command "_circle" "3516.053,874.7" "0.15")
(command "_circle" "3517.928,876.7" "0.075")
(command "_circle" "3517.553,876.7" "0.075")
(command "_circle" "3517.178,876.7" "0.075")
(command "_circle" "3516.803,876.7" "0.15")
(command "_circle" "3516.428,876.7" "0.075")
(command "_circle" "3516.053,876.7" "0.15")
(command "_circle" "3517.928,878.7" "0.075")
(command "_circle" "3517.553,878.7" "0.15")
(command "_circle" "3517.178,878.7" "0.075")
(command "_circle" "3516.803,878.7" "0.15")
(command "_circle" "3516.428,878.7" "0.075")
(command "_circle" "3516.053,878.7" "0.15")
(command "_circle" "3517.928,880.7" "0.075")
(command "_circle" "3517.553,880.7" "0.075")
(command "_circle" "3517.178,880.7" "0.15")
(command "_circle" "3516.803,880.7" "0.15")
(command "_circle" "3516.428,880.7" "0.075")
(command "_circle" "3516.053,880.7" "0.15")
(command "_circle" "3517.928,882.7" "0.075")
(command "_circle" "3517.553,882.7" "0.15")
(command "_circle" "3517.178,882.7" "0.15")
(command "_circle" "3516.803,882.7" "0.15")
(command "_circle" "3516.428,882.7" "0.075")
(command "_circle" "3516.053,882.7" "0.15")
(command "_circle" "3517.928,884.7" "0.075")
(command "_circle" "3517.553,884.7" "0.075")
(command "_circle" "3517.178,884.7" "0.075")
(command "_circle" "3516.803,884.7" "0.075")
(command "_circle" "3516.428,884.7" "0.15")
(command "_circle" "3516.053,884.7" "0.15")
(command "_circle" "3517.928,886.7" "0.075")
(command "_circle" "3517.553,886.7" "0.15")
(command "_circle" "3517.178,886.7" "0.075")
(command "_circle" "3516.803,886.7" "0.075")
(command "_circle" "3516.428,886.7" "0.15")
(command "_circle" "3516.053,886.7" "0.15")
(command "_circle" "3517.928,888.7" "0.075")
(command "_circle" "3517.553,888.7" "0.075")
(command "_circle" "3517.178,888.7" "0.15")
(command "_circle" "3516.803,888.7" "0.075")
(command "_circle" "3516.428,888.7" "0.15")
(command "_circle" "3516.053,888.7" "0.15")
(command "_circle" "3517.928,890.7" "0.075")
(command "_circle" "3517.553,890.7" "0.15")
(command "_circle" "3517.178,890.7" "0.15")
(command "_circle" "3516.803,890.7" "0.075")
(command "_circle" "3516.428,890.7" "0.15")
(command "_circle" "3516.053,890.7" "0.15")
(command "_circle" "3517.928,892.7" "0.075")
(command "_circle" "3517.553,892.7" "0.075")
(command "_circle" "3517.178,892.7" "0.075")
(command "_circle" "3516.803,892.7" "0.15")
(command "_circle" "3516.428,892.7" "0.15")
(command "_circle" "3516.053,892.7" "0.15")
(command "_circle" "3517.928,894.7" "0.075")
(command "_circle" "3517.553,894.7" "0.15")
(command "_circle" "3517.178,894.7" "0.075")
(command "_circle" "3516.803,894.7" "0.15")
(command "_circle" "3516.428,894.7" "0.15")
(command "_circle" "3516.053,894.7" "0.15")
(command "_circle" "3517.928,896.7" "0.075")
(command "_circle" "3517.553,896.7" "0.075")
(command "_circle" "3517.178,896.7" "0.15")
(command "_circle" "3516.803,896.7" "0.15")
(command "_circle" "3516.428,896.7" "0.15")
(command "_circle" "3516.053,896.7" "0.15")
(command "_circle" "3517.928,898.7" "0.075")
(command "_circle" "3517.553,898.7" "0.15")
(command "_circle" "3517.178,898.7" "0.15")
(command "_circle" "3516.803,898.7" "0.15")
(command "_circle" "3516.428,898.7" "0.15")
(command "_circle" "3516.053,898.7" "0.15")
(command "_circle" "3517.928,900.7" "0.075")
(command "_circle" "3517.553,900.7" "0.075")
(command "_circle" "3517.178,900.7" "0.075")
(command "_circle" "3516.803,900.7" "0.075")
(command "_circle" "3516.428,900.7" "0.075")
(command "_circle" "3516.053,900.7" "0.075")
(command "_circle" "3515.678,900.7" "0.15")
(command "_circle" "3517.928,902.7" "0.075")
(command "_circle" "3517.553,902.7" "0.15")
(command "_circle" "3517.178,902.7" "0.075")
(command "_circle" "3516.803,902.7" "0.075")
(command "_circle" "3516.428,902.7" "0.075")
(command "_circle" "3516.053,902.7" "0.075")
(command "_circle" "3515.678,902.7" "0.15")
(command "_circle" "3517.928,904.7" "0.075")
(command "_circle" "3517.553,904.7" "0.075")
(command "_circle" "3517.178,904.7" "0.15")
(command "_circle" "3516.803,904.7" "0.075")
(command "_circle" "3516.428,904.7" "0.075")
(command "_circle" "3516.053,904.7" "0.075")
(command "_circle" "3515.678,904.7" "0.15")
(command "_circle" "3517.928,906.7" "0.075")
(command "_circle" "3517.553,906.7" "0.15")
(command "_circle" "3517.178,906.7" "0.15")
(command "_circle" "3516.803,906.7" "0.075")
(command "_circle" "3516.428,906.7" "0.075")
(command "_circle" "3516.053,906.7" "0.075")
(command "_circle" "3515.678,906.7" "0.15")
(command "_circle" "3517.928,908.7" "0.075")
(command "_circle" "3517.553,908.7" "0.075")
(command "_circle" "3517.178,908.7" "0.075")
(command "_circle" "3516.803,908.7" "0.15")
(command "_circle" "3516.428,908.7" "0.075")
(command "_circle" "3516.053,908.7" "0.075")
(command "_circle" "3515.678,908.7" "0.15")
(command "_circle" "3517.928,910.7" "0.075")
(command "_circle" "3517.553,910.7" "0.15")
(command "_circle" "3517.178,910.7" "0.075")
(command "_circle" "3516.803,910.7" "0.15")
(command "_circle" "3516.428,910.7" "0.075")
(command "_circle" "3516.053,910.7" "0.075")
(command "_circle" "3515.678,910.7" "0.15")
(command "_circle" "3517.928,912.7" "0.075")
(command "_circle" "3517.553,912.7" "0.075")
(command "_circle" "3517.178,912.7" "0.15")
(command "_circle" "3516.803,912.7" "0.15")
(command "_circle" "3516.428,912.7" "0.075")
(command "_circle" "3516.053,912.7" "0.075")
(command "_circle" "3515.678,912.7" "0.15")
(command "_circle" "3517.928,914.7" "0.075")
(command "_circle" "3517.553,914.7" "0.15")
(command "_circle" "3517.178,914.7" "0.15")
(command "_circle" "3516.803,914.7" "0.15")
(command "_circle" "3516.428,914.7" "0.075")
(command "_circle" "3516.053,914.7" "0.075")
(command "_circle" "3515.678,914.7" "0.15")
(command "_circle" "3517.928,916.7" "0.075")
(command "_circle" "3517.553,916.7" "0.075")
(command "_circle" "3517.178,916.7" "0.075")
(command "_circle" "3516.803,916.7" "0.075")
(command "_circle" "3516.428,916.7" "0.15")
(command "_circle" "3516.053,916.7" "0.075")
(command "_circle" "3515.678,916.7" "0.15")
(command "_circle" "3517.928,918.7" "0.075")
(command "_circle" "3517.553,918.7" "0.15")
(command "_circle" "3517.178,918.7" "0.075")
(command "_circle" "3516.803,918.7" "0.075")
(command "_circle" "3516.428,918.7" "0.15")
(command "_circle" "3516.053,918.7" "0.075")
(command "_circle" "3515.678,918.7" "0.15")
(command "_circle" "3517.928,920.7" "0.075")
(command "_circle" "3517.553,920.7" "0.075")
(command "_circle" "3517.178,920.7" "0.15")
(command "_circle" "3516.803,920.7" "0.075")
(command "_circle" "3516.428,920.7" "0.15")
(command "_circle" "3516.053,920.7" "0.075")
(command "_circle" "3515.678,920.7" "0.15")
(command "_circle" "3517.928,922.7" "0.075")
(command "_circle" "3517.553,922.7" "0.15")
(command "_circle" "3517.178,922.7" "0.15")
(command "_circle" "3516.803,922.7" "0.075")
(command "_circle" "3516.428,922.7" "0.15")
(command "_circle" "3516.053,922.7" "0.075")
(command "_circle" "3515.678,922.7" "0.15")
(command "_circle" "3517.928,924.7" "0.075")
(command "_circle" "3517.553,924.7" "0.075")
(command "_circle" "3517.178,924.7" "0.075")
(command "_circle" "3516.803,924.7" "0.15")
(command "_circle" "3516.428,924.7" "0.15")
(command "_circle" "3516.053,924.7" "0.075")
(command "_circle" "3515.678,924.7" "0.15")
(command "_circle" "3517.928,926.7" "0.075")
(command "_circle" "3517.553,926.7" "0.15")
(command "_circle" "3517.178,926.7" "0.075")
(command "_circle" "3516.803,926.7" "0.15")
(command "_circle" "3516.428,926.7" "0.15")
(command "_circle" "3516.053,926.7" "0.075")
(command "_circle" "3515.678,926.7" "0.15")
(command "_circle" "3517.928,928.7" "0.075")
(command "_circle" "3517.553,928.7" "0.075")
(command "_circle" "3517.178,928.7" "0.15")
(command "_circle" "3516.803,928.7" "0.15")
(command "_circle" "3516.428,928.7" "0.15")
(command "_circle" "3516.053,928.7" "0.075")
(command "_circle" "3515.678,928.7" "0.15")
(command "_circle" "3517.928,930.7" "0.075")
(command "_circle" "3517.553,930.7" "0.15")
(command "_circle" "3517.178,930.7" "0.15")
(command "_circle" "3516.803,930.7" "0.15")
(command "_circle" "3516.428,930.7" "0.15")
(command "_circle" "3516.053,930.7" "0.075")
(command "_circle" "3515.678,930.7" "0.15")
(command "_circle" "3517.928,932.7" "0.075")
(command "_circle" "3517.553,932.7" "0.075")
(command "_circle" "3517.178,932.7" "0.075")
(command "_circle" "3516.803,932.7" "0.075")
(command "_circle" "3516.428,932.7" "0.075")
(command "_circle" "3516.053,932.7" "0.15")
(command "_circle" "3515.678,932.7" "0.15")
(command "_circle" "3517.928,934.7" "0.075")
(command "_circle" "3517.553,934.7" "0.15")
(command "_circle" "3517.178,934.7" "0.075")
(command "_circle" "3516.803,934.7" "0.075")
(command "_circle" "3516.428,934.7" "0.075")
(command "_circle" "3516.053,934.7" "0.15")
(command "_circle" "3515.678,934.7" "0.15")
(command "_circle" "3517.928,936.7" "0.075")
(command "_circle" "3517.553,936.7" "0.075")
(command "_circle" "3517.178,936.7" "0.15")
(command "_circle" "3516.803,936.7" "0.075")
(command "_circle" "3516.428,936.7" "0.075")
(command "_circle" "3516.053,936.7" "0.15")
(command "_circle" "3515.678,936.7" "0.15")
(command "_circle" "3517.928,938.7" "0.075")
(command "_circle" "3517.553,938.7" "0.15")
(command "_circle" "3517.178,938.7" "0.15")
(command "_circle" "3516.803,938.7" "0.075")
(command "_circle" "3516.428,938.7" "0.075")
(command "_circle" "3516.053,938.7" "0.15")
(command "_circle" "3515.678,938.7" "0.15")
(command "_circle" "3517.928,940.7" "0.075")
(command "_circle" "3517.553,940.7" "0.075")
(command "_circle" "3517.178,940.7" "0.075")
(command "_circle" "3516.803,940.7" "0.15")
(command "_circle" "3516.428,940.7" "0.075")
(command "_circle" "3516.053,940.7" "0.15")
(command "_circle" "3515.678,940.7" "0.15")
(command "_circle" "3517.928,942.7" "0.075")
(command "_circle" "3517.553,942.7" "0.15")
(command "_circle" "3517.178,942.7" "0.075")
(command "_circle" "3516.803,942.7" "0.15")
(command "_circle" "3516.428,942.7" "0.075")
(command "_circle" "3516.053,942.7" "0.15")
(command "_circle" "3515.678,942.7" "0.15")
(command "_circle" "3517.928,944.7" "0.075")
(command "_circle" "3517.553,944.7" "0.075")
(command "_circle" "3517.178,944.7" "0.15")
(command "_circle" "3516.803,944.7" "0.15")
(command "_circle" "3516.428,944.7" "0.075")
(command "_circle" "3516.053,944.7" "0.15")
(command "_circle" "3515.678,944.7" "0.15")
(command "_circle" "3517.928,946.7" "0.075")
(command "_circle" "3517.553,946.7" "0.15")
(command "_circle" "3517.178,946.7" "0.15")
(command "_circle" "3516.803,946.7" "0.15")
(command "_circle" "3516.428,946.7" "0.075")
(command "_circle" "3516.053,946.7" "0.15")
(command "_circle" "3515.678,946.7" "0.15")
(command "_circle" "3517.928,948.7" "0.075")
(command "_circle" "3517.553,948.7" "0.075")
(command "_circle" "3517.178,948.7" "0.075")
(command "_circle" "3516.803,948.7" "0.075")
(command "_circle" "3516.428,948.7" "0.15")
(command "_circle" "3516.053,948.7" "0.15")
(command "_circle" "3515.678,948.7" "0.15")
(command "_circle" "3517.928,950.7" "0.075")
(command "_circle" "3517.553,950.7" "0.15")
(command "_circle" "3517.178,950.7" "0.075")
(command "_circle" "3516.803,950.7" "0.075")
(command "_circle" "3516.428,950.7" "0.15")
(command "_circle" "3516.053,950.7" "0.15")
(command "_circle" "3515.678,950.7" "0.15")
(command "_circle" "3517.928,952.7" "0.075")
(command "_circle" "3517.553,952.7" "0.075")
(command "_circle" "3517.178,952.7" "0.15")
(command "_circle" "3516.803,952.7" "0.075")
(command "_circle" "3516.428,952.7" "0.15")
(command "_circle" "3516.053,952.7" "0.15")
(command "_circle" "3515.678,952.7" "0.15")
(command "_circle" "3517.928,954.7" "0.075")
(command "_circle" "3517.553,954.7" "0.15")
(command "_circle" "3517.178,954.7" "0.15")
(command "_circle" "3516.803,954.7" "0.075")
(command "_circle" "3516.428,954.7" "0.15")
(command "_circle" "3516.053,954.7" "0.15")
(command "_circle" "3515.678,954.7" "0.15")
(command "_circle" "3517.928,956.7" "0.075")
(command "_circle" "3517.553,956.7" "0.075")
(command "_circle" "3517.178,956.7" "0.075")
(command "_circle" "3516.803,956.7" "0.15")
(command "_circle" "3516.428,956.7" "0.15")
(command "_circle" "3516.053,956.7" "0.15")
(command "_circle" "3515.678,956.7" "0.15")
(command "_circle" "3517.928,958.7" "0.075")
(command "_circle" "3517.553,958.7" "0.15")
(command "_circle" "3517.178,958.7" "0.075")
(command "_circle" "3516.803,958.7" "0.15")
(command "_circle" "3516.428,958.7" "0.15")
(command "_circle" "3516.053,958.7" "0.15")
(command "_circle" "3515.678,958.7" "0.15")
(command "_circle" "3517.928,960.7" "0.075")
(command "_circle" "3517.553,960.7" "0.075")
(command "_circle" "3517.178,960.7" "0.15")
(command "_circle" "3516.803,960.7" "0.15")
(command "_circle" "3516.428,960.7" "0.15")
(command "_circle" "3516.053,960.7" "0.15")
(command "_circle" "3515.678,960.7" "0.15")
(command "_circle" "3517.928,962.7" "0.075")
(command "_circle" "3517.553,962.7" "0.15")
(command "_circle" "3517.178,962.7" "0.15")
(command "_circle" "3516.803,962.7" "0.15")
(command "_circle" "3516.428,962.7" "0.15")
(command "_circle" "3516.053,962.7" "0.15")
(command "_circle" "3515.678,962.7" "0.15")
(command "_layer" "set" "nitride" "")
(command "_layer" "set" "text" "")
(command-s "_text" "3506.878,963.3" "2" "-90" "a = 370 nm" )
(sssetfirst nil (ssget "_L"))
(if (not (numberp (vl-string-search "Mac" (getvar "platform")))) (c:txtexp))
(command "_layer" "set" "nitride" "")
(command "_layer" "set" "text" "")
(command-s "_text" "3503.878,963.3" "2" "-90" "gap = 250 nm" )
(sssetfirst nil (ssget "_L"))
(if (not (numberp (vl-string-search "Mac" (getvar "platform")))) (c:txtexp))
(command "_layer" "set" "nitride" "")
(command "_layer" "set" "text" "")
(command-s "_text" "3500.878,963.3" "2" "-90" "amplitude = 137 nm" )
(sssetfirst nil (ssget "_L"))
(if (not (numberp (vl-string-search "Mac" (getvar "platform")))) (c:txtexp))
(command "_layer" "set" "nitride" "")
(command "_layer" "set" "text" "")
(command-s "_text" "3497.878,963.3" "2" "-90" "start width = 280 nm" )
(sssetfirst nil (ssget "_L"))
(if (not (numberp (vl-string-search "Mac" (getvar "platform")))) (c:txtexp))
(command "_layer" "set" "nitride" "")
(command "_layer" "set" "text" "")
(command-s "_text" "3494.878,963.3" "2" "-90" "width = 299 nm" )
(sssetfirst nil (ssget "_L"))
(if (not (numberp (vl-string-search "Mac" (getvar "platform")))) (c:txtexp))
(command "_layer" "set" "nitride" "")
(command "_layer" "set" "text" "")
(command-s "_text" "3491.878,963.3" "2" "-90" "taper: 15" )
(sssetfirst nil (ssget "_L"))
(if (not (numberp (vl-string-search "Mac" (getvar "platform")))) (c:txtexp))
(command "_layer" "set" "nitride" "")
(command "_layer" "set" "text" "")
(command-s "_text" "3488.878,963.3" "2" "-90" "nominal: 150" )
(sssetfirst nil (ssget "_L"))
(if (not (numberp (vl-string-search "Mac" (getvar "platform")))) (c:txtexp))
(command "_layer" "set" "nitride" "")
(command "_layer" "set" "indicators" "")
(setq coords (list 
(list 3440.415 940) 
(list 3440.415 920) 
(list 3420.415 900) 
(list 3440.415 880) 
(list 3440.415 860) 
(list 3440.415 900) 
(list 3440.415 887.0711) 
(list 3427.4861 900) 
(list 3440.415 912.9289) 
(list 3440.415 900)))
(apply 'command (append '("pline") coords '("c")))
(command "._fillet" "radius" "1" "._fillet" "P" (entlast))
(setq coords (list 
(list 3599.585 940) 
(list 3599.585 920) 
(list 3619.585 900) 
(list 3599.585 880) 
(list 3599.585 860) 
(list 3599.585 900) 
(list 3599.585 887.0711) 
(list 3612.5139 900) 
(list 3599.585 912.9289) 
(list 3599.585 900)))
(apply 'command (append '("pline") coords '("c")))
(command "._fillet" "radius" "1" "._fillet" "P" (entlast))
(command "_layer" "set" "holes" "")
(command "_circle" "3438.0629,914.1124" "0.5")
(command "_circle" "3435.7109,911.7603" "0.5")
(command "_circle" "3433.3588,909.4083" "0.5")
(command "_circle" "3431.0067,907.0562" "0.5")
(command "_circle" "3428.6547,904.7041" "0.5")
(command "_circle" "3426.3026,902.3521" "0.5")
(command "_circle" "3423.9505,900" "0.5")
(command "_circle" "3426.3026,897.6479" "0.5")
(command "_circle" "3428.6547,895.2959" "0.5")
(command "_circle" "3431.0067,892.9438" "0.5")
(command "_circle" "3433.3588,890.5917" "0.5")
(command "_circle" "3435.7109,888.2397" "0.5")
(command "_circle" "3438.0629,885.8876" "0.5")
(command "_circle" "3601.9371,914.1124" "0.5")
(command "_circle" "3604.2891,911.7603" "0.5")
(command "_circle" "3606.6412,909.4083" "0.5")
(command "_circle" "3608.9933,907.0562" "0.5")
(command "_circle" "3611.3453,904.7041" "0.5")
(command "_circle" "3613.6974,902.3521" "0.5")
(command "_circle" "3616.0495,900" "0.5")
(command "_circle" "3613.6974,897.6479" "0.5")
(command "_circle" "3611.3453,895.2959" "0.5")
(command "_circle" "3608.9933,892.9438" "0.5")
(command "_circle" "3606.6412,890.5917" "0.5")
(command "_circle" "3604.2891,888.2397" "0.5")
(command "_circle" "3601.9371,885.8876" "0.5")
(command "_layer" "set" "nitride" "")
(command "_block" "blkcoupler11" "3520,900" coupler11 "")
(command "_insert" "blkcoupler11" "3520,900" "1" "1" "0")
(command "_insert" "blkcoupler11" "3520,900" "1" "1" "180")
(command "_block" "blksinglenanobeam11" "3520,900" singlenanobeam11 "")
(command "_insert" "blksinglenanobeam11" "3520,900" "1" "1" "0")
(command "_insert" "blksinglenanobeam11" "3520,900" "1" "1" "180")
(command "_block" "blkanglednodearray11" "3520,900" anglednodearray11 "")
(command "_insert" "blkanglednodearray11" "3520,900" "1" "1" "0")
(command "_insert" "blkanglednodearray11" "3520,900" "1" "1" "180")
(command "_block" "blkcooledsinglenanobeam11" "3520,900" cooledsinglenanobeam11 "")
(command "_insert" "blkcooledsinglenanobeam11" "3520,900" "1" "1" "0")
(command "_insert" "blkcooledsinglenanobeam11" "3520,900" "1" "1" "180")
(command "_block" "blkyjunction11" "3520,900" yjunction11 "")
(command "_insert" "blkyjunction11" "3520,900" "1" "1" "0")
(command "_insert" "blkyjunction11" "3520,900" "1" "1" "180")
; DRAWING BULGING VEE GROOVE
(command "_layer" "set" "vgroove" "")
(setq coords (list 
(list 3445.415 -605) 
(list 3445.415 0) 
(list 3445.415 0) 
(list 3445.415 1800) 
(list 3445.415 1800) 
(list 3445.415 2405) 
(list 3594.585 2405) 
(list 3594.585 1800) 
(list 3594.585 1800) 
(list 3594.585 0) 
(list 3594.585 0) 
(list 3594.585 -605)))
(apply 'command (append '("pline") coords '("c")))
(command "._fillet" "radius" "0" "._fillet" "P" (entlast))
(command "_layer" "set" "window" "")
(command "_rectangle" "3445.415,-1935" "3594.585,-600")
(command "_rectangle" "3445.415,2400" "3594.585,5300")
(command "_layer" "set" "grid" "")
(command "_rectangle" "3446.415,-1934" "3469.9433,-1909.2133")
(command "_array" "last" "" "R" "75" "3" "25.7867" "24.5283")
(command "_rectangle" "3521,-1934" "3544.5283,-1909.2133")
(command "_array" "last" "" "R" "75" "3" "25.7867" "24.5283")
(command "_rectangle" "3446.415,1" "3469.9433,25.7")
(command "_array" "last" "" "R" "70" "3" "25.7" "24.5283")
(command "_rectangle" "3521,1" "3544.5283,25.7")
(command "_array" "last" "" "R" "70" "3" "25.7" "24.5283")
(command "_rectangle" "3446.415,1801" "3469.9433,1825.9185")
(command "_array" "last" "" "R" "135" "3" "25.9185" "24.5283")
(command "_rectangle" "3521,1801" "3544.5283,1825.9185")
(command "_array" "last" "" "R" "135" "3" "25.9185" "24.5283")
(command "_layer" "set" "vgrooveFDA" "")
(command "_rectangle" "3594.585,-2233" "3445.415,-1933")
(command "_layer" "set" "nitride" "")
(command "_layer" "set" "holes" "")
(command "_circle" "3597.085,331.5" "0.5")
(command "_array" "last" "" "R" "379" "1" "3" "2.5")
(command "_circle" "3442.915,331.5" "0.5")
(command "_array" "last" "" "R" "379" "1" "3" "-2.5")
(command "_layer" "set" "nitride" "")
(command "_layer" "set" "window" "")
(command "_layer" "set" "window" "")
(command "_rectangle" "3599.585,0" "3760.415,1800")
(command "._fillet" "radius" "20" "._fillet" "P" (entlast))
(command "_layer" "set" "grid" "")
(command "_rectangle" "3600.585,1" "3622.4179,25.7")
(command "_array" "last" "" "R" "70" "7" "25.7" "22.8329")
(command "_layer" "set" "nitride" "")
; DRAWING REGION LAYER
(command "_layer" "set" "regionLayer11" "")
(command "_rectangle" "3440,-460" "3600,2260")
(command "_layer" "set" "nitride" "")
(setq coupler11 nil)
(setq singlenanobeam11 nil)
(setq anglednodearray11 nil)
(setq cooledsinglenanobeam11 nil)
(setq yjunction11 nil)
; DEVICE #12
(command "_layer" "set" "window" "")
(command "_circle" "3752.915,-415" "5")
(command "_circle" "3752.915,-402.5" "5")
(command "_circle" "3752.915,-390" "5")
(command "_circle" "3752.915,-377.5" "5")
(command "_circle" "3740.415,-415" "5")
(command "_circle" "3740.415,-402.5" "5")
(command "_circle" "3740.415,-390" "5")
(command "_circle" "3740.415,-377.5" "5")
(command "_circle" "3727.915,-415" "5")
(command "_circle" "3727.915,-402.5" "5")
(command "_circle" "3727.915,-390" "5")
(command "_circle" "3727.915,-377.5" "5")
(command "_layer" "set" "nitride" "")
(setq currobj nil)
(setq currobj (ssadd))
; DRAWING COUPLER
(setq coords (list 
(list 3840.0655 -415) 
(list 3840.0655 -413) 
(list 3913.585 -413) 
(list 3913.585 -413) 
(list 3913.9677 -413.0761) 
(list 3914.2921 -413.2929) 
(list 3914.5089 -413.6173) 
(list 3914.585 -414) 
(list 3914.585 -411.8) 
(list 3914.585 -411.8) 
(list 3914.5089 -412.1827) 
(list 3914.2921 -412.5071) 
(list 3913.9677 -412.7239) 
(list 3913.585 -412.8) 
(list 3840.0655 -412.8) 
(list 3840.0655 -410.8) 
(list 3839.9345 -410.8) 
(list 3839.9345 -412.8) 
(list 3766.415 -412.8) 
(list 3766.0323 -412.7239) 
(list 3765.7079 -412.5071) 
(list 3765.4911 -412.1827) 
(list 3765.415 -411.8) 
(list 3765.415 -411.8) 
(list 3765.415 -414) 
(list 3765.4911 -413.6173) 
(list 3765.7079 -413.2929) 
(list 3766.0323 -413.0761) 
(list 3766.415 -413) 
(list 3766.415 -413) 
(list 3839.9345 -413) 
(list 3839.9345 -415)))
(apply 'command (append '("pline") coords '("c")))
(setq currobj (ssadd (entlast) currobj))
(command "._fillet" "radius" "0.3" "._fillet" "P" (entlast))
(command "_layer" "set" "holes" "")
(command "_circle" "3840,-412.9" "0.113")
(setq currobj (ssadd (entlast) currobj))
(command "_layer" "set" "nitride" "")
(command "_layer" "set" "text" "")
(command "_circle" "3839.2,-415" "0.075")
(command "_circle" "3839.2,-414.7" "0.075")
(command "_circle" "3839.2,-414.4" "0.075")
(command "_circle" "3838.9,-415" "0.075")
(command "_circle" "3838.9,-414.7" "0.075")
(command "_circle" "3838.9,-414.4" "0.075")
(command "_circle" "3838.6,-415" "0.075")
(command "_circle" "3838.6,-414.7" "0.075")
(command "_circle" "3838.6,-414.4" "0.075")
(command "_layer" "set" "nitride" "")
(command "_layer" "set" "prebias" "")
(command "_rectangle" "3765.415,-414" "3914.585,-411.8")
(setq currobj (ssadd (entlast) currobj))
(command "_rectangle" "3839.9345,-415" "3840.0655,-410.8")
(setq currobj (ssadd (entlast) currobj))
(command "_layer" "set" "nitride" "")
(setq coupler12 currobj)
(setq currobj nil)
(setq currobj (ssadd))
; DRAWING SINGLE NANOBEAM
(setq coords (list 
(list 3840.0655 -410.8) 
(list 3840.0655 -409.1417) 
(list 3840.0655 -407.4833) 
(list 3840.0655 -405.825) 
(list 3840.0655 -404.1667) 
(list 3840.0655 -402.5083) 
(list 3840.0655 -400.85) 
(list 3840.0655 -399.1917) 
(list 3840.0655 -397.5333) 
(list 3840.0655 -395.875) 
(list 3840.0656 -394.2167) 
(list 3840.0656 -392.5583) 
(list 3840.0656 -390.9) 
(list 3840.0657 -389.2417) 
(list 3840.0657 -387.5833) 
(list 3840.0657 -385.925) 
(list 3840.0658 -384.2667) 
(list 3840.0658 -382.6083) 
(list 3840.0659 -380.95) 
(list 3840.066 -379.2917) 
(list 3840.0661 -377.6333) 
(list 3840.0661 -375.975) 
(list 3840.0662 -374.3167) 
(list 3840.0663 -372.6583) 
(list 3840.0665 -371) 
(list 3840.0666 -369.3417) 
(list 3840.0667 -367.6833) 
(list 3840.0669 -366.025) 
(list 3840.067 -364.3667) 
(list 3840.0672 -362.7083) 
(list 3840.0674 -361.05) 
(list 3840.0676 -359.3917) 
(list 3840.0678 -357.7333) 
(list 3840.068 -356.075) 
(list 3840.0682 -354.4167) 
(list 3840.0685 -352.7583) 
(list 3840.0687 -351.1) 
(list 3840.069 -349.4417) 
(list 3840.0693 -347.7833) 
(list 3840.0696 -346.125) 
(list 3840.0699 -344.4667) 
(list 3840.0703 -342.8083) 
(list 3840.0706 -341.15) 
(list 3840.071 -339.4917) 
(list 3840.0714 -337.8333) 
(list 3840.0718 -336.175) 
(list 3840.0722 -334.5167) 
(list 3840.0727 -332.8583) 
(list 3840.0731 -331.2) 
(list 3840.0736 -329.5417) 
(list 3840.0741 -327.8833) 
(list 3840.0747 -326.225) 
(list 3840.0752 -324.5667) 
(list 3840.0758 -322.9083) 
(list 3840.0764 -321.25) 
(list 3840.077 -319.5917) 
(list 3840.0776 -317.9333) 
(list 3840.0783 -316.275) 
(list 3840.079 -314.6167) 
(list 3840.0797 -312.9583) 
(list 3840.0804 -311.3) 
(list 3840.0812 -309.6417) 
(list 3840.082 -307.9833) 
(list 3840.0828 -306.325) 
(list 3840.0836 -304.6667) 
(list 3840.0845 -303.0083) 
(list 3840.0854 -301.35) 
(list 3840.0863 -299.6917) 
(list 3840.0872 -298.0333) 
(list 3840.0882 -296.375) 
(list 3840.0892 -294.7167) 
(list 3840.0903 -293.0583) 
(list 3840.0913 -291.4) 
(list 3840.0924 -289.7417) 
(list 3840.0935 -288.0833) 
(list 3840.0947 -286.425) 
(list 3840.0959 -284.7667) 
(list 3840.0971 -283.1083) 
(list 3840.0983 -281.45) 
(list 3840.0996 -279.7917) 
(list 3840.1009 -278.1333) 
(list 3840.1023 -276.475) 
(list 3840.1036 -274.8167) 
(list 3840.105 -273.1583) 
(list 3840.1065 -271.5) 
(list 3840.108 -269.8417) 
(list 3840.1095 -268.1833) 
(list 3840.111 -266.525) 
(list 3840.1126 -264.8667) 
(list 3840.1143 -263.2083) 
(list 3840.1159 -261.55) 
(list 3840.1176 -259.8917) 
(list 3840.1193 -258.2333) 
(list 3840.1211 -256.575) 
(list 3840.1229 -254.9167) 
(list 3840.1248 -253.2583) 
(list 3840.1267 -251.6) 
(list 3840.1286 -249.9417) 
(list 3840.1306 -248.2833) 
(list 3840.1326 -246.625) 
(list 3840.1347 -244.9667) 
(list 3840.1368 -243.3083) 
(list 3840.1389 -241.65) 
(list 3840.1411 -239.9917) 
(list 3840.1433 -238.3333) 
(list 3840.1456 -236.675) 
(list 3840.1479 -235.0167) 
(list 3840.1502 -233.3583) 
(list 3840.1526 -231.7) 
(list 3840.1551 -230.0417) 
(list 3840.1575 -228.3833) 
(list 3840.1601 -226.725) 
(list 3840.1627 -225.0667) 
(list 3840.1653 -223.4083) 
(list 3840.168 -221.75) 
(list 3840.1707 -220.0917) 
(list 3840.1734 -218.4333) 
(list 3840.1763 -216.775) 
(list 3840.1791 -215.1167) 
(list 3840.182 -213.4583) 
(list 3840.185 -211.8) 
(list 3839.815 -211.8) 
(list 3839.818 -213.4583) 
(list 3839.8209 -215.1167) 
(list 3839.8237 -216.775) 
(list 3839.8266 -218.4333) 
(list 3839.8293 -220.0917) 
(list 3839.832 -221.75) 
(list 3839.8347 -223.4083) 
(list 3839.8373 -225.0667) 
(list 3839.8399 -226.725) 
(list 3839.8425 -228.3833) 
(list 3839.8449 -230.0417) 
(list 3839.8474 -231.7) 
(list 3839.8498 -233.3583) 
(list 3839.8521 -235.0167) 
(list 3839.8544 -236.675) 
(list 3839.8567 -238.3333) 
(list 3839.8589 -239.9917) 
(list 3839.8611 -241.65) 
(list 3839.8632 -243.3083) 
(list 3839.8653 -244.9667) 
(list 3839.8674 -246.625) 
(list 3839.8694 -248.2833) 
(list 3839.8714 -249.9417) 
(list 3839.8733 -251.6) 
(list 3839.8752 -253.2583) 
(list 3839.8771 -254.9167) 
(list 3839.8789 -256.575) 
(list 3839.8807 -258.2333) 
(list 3839.8824 -259.8917) 
(list 3839.8841 -261.55) 
(list 3839.8857 -263.2083) 
(list 3839.8874 -264.8667) 
(list 3839.889 -266.525) 
(list 3839.8905 -268.1833) 
(list 3839.892 -269.8417) 
(list 3839.8935 -271.5) 
(list 3839.895 -273.1583) 
(list 3839.8964 -274.8167) 
(list 3839.8977 -276.475) 
(list 3839.8991 -278.1333) 
(list 3839.9004 -279.7917) 
(list 3839.9017 -281.45) 
(list 3839.9029 -283.1083) 
(list 3839.9041 -284.7667) 
(list 3839.9053 -286.425) 
(list 3839.9065 -288.0833) 
(list 3839.9076 -289.7417) 
(list 3839.9087 -291.4) 
(list 3839.9097 -293.0583) 
(list 3839.9108 -294.7167) 
(list 3839.9118 -296.375) 
(list 3839.9128 -298.0333) 
(list 3839.9137 -299.6917) 
(list 3839.9146 -301.35) 
(list 3839.9155 -303.0083) 
(list 3839.9164 -304.6667) 
(list 3839.9172 -306.325) 
(list 3839.918 -307.9833) 
(list 3839.9188 -309.6417) 
(list 3839.9196 -311.3) 
(list 3839.9203 -312.9583) 
(list 3839.921 -314.6167) 
(list 3839.9217 -316.275) 
(list 3839.9224 -317.9333) 
(list 3839.923 -319.5917) 
(list 3839.9236 -321.25) 
(list 3839.9242 -322.9083) 
(list 3839.9248 -324.5667) 
(list 3839.9253 -326.225) 
(list 3839.9259 -327.8833) 
(list 3839.9264 -329.5417) 
(list 3839.9269 -331.2) 
(list 3839.9273 -332.8583) 
(list 3839.9278 -334.5167) 
(list 3839.9282 -336.175) 
(list 3839.9286 -337.8333) 
(list 3839.929 -339.4917) 
(list 3839.9294 -341.15) 
(list 3839.9297 -342.8083) 
(list 3839.9301 -344.4667) 
(list 3839.9304 -346.125) 
(list 3839.9307 -347.7833) 
(list 3839.931 -349.4417) 
(list 3839.9313 -351.1) 
(list 3839.9315 -352.7583) 
(list 3839.9318 -354.4167) 
(list 3839.932 -356.075) 
(list 3839.9322 -357.7333) 
(list 3839.9324 -359.3917) 
(list 3839.9326 -361.05) 
(list 3839.9328 -362.7083) 
(list 3839.933 -364.3667) 
(list 3839.9331 -366.025) 
(list 3839.9333 -367.6833) 
(list 3839.9334 -369.3417) 
(list 3839.9335 -371) 
(list 3839.9337 -372.6583) 
(list 3839.9338 -374.3167) 
(list 3839.9339 -375.975) 
(list 3839.9339 -377.6333) 
(list 3839.934 -379.2917) 
(list 3839.9341 -380.95) 
(list 3839.9342 -382.6083) 
(list 3839.9342 -384.2667) 
(list 3839.9343 -385.925) 
(list 3839.9343 -387.5833) 
(list 3839.9343 -389.2417) 
(list 3839.9344 -390.9) 
(list 3839.9344 -392.5583) 
(list 3839.9344 -394.2167) 
(list 3839.9345 -395.875) 
(list 3839.9345 -397.5333) 
(list 3839.9345 -399.1917) 
(list 3839.9345 -400.85) 
(list 3839.9345 -402.5083) 
(list 3839.9345 -404.1667) 
(list 3839.9345 -405.825) 
(list 3839.9345 -407.4833) 
(list 3839.9345 -409.1417) 
(list 3839.9345 -410.8)))
(apply 'command (append '("pline") coords '("c")))
(setq currobj (ssadd (entlast) currobj))
(command "_layer" "set" "prebias" "")
(command "_rectangle" "3839.815,-410.8" "3840.185,-211.8")
(setq currobj (ssadd (entlast) currobj))
(command "_layer" "set" "nitride" "")
(setq singlenanobeam12 currobj)
(setq currobj nil)
(setq currobj (ssadd))
; DRAWING NODE ARRAY
(setq coords (list 
(list 3840.185 -211.8) 
(list 3840.5625 -201.8) 
(list 3840.5625 -201.8) 
(list 3840.5625 -200.8) 
(list 3914.585 -212.6864) 
(list 3914.585 -207.7434) 
(list 3840.5625 -197.357) 
(list 3840.5625 -196.357) 
(list 3840.5625 -196.357) 
(list 3840.2625 -186.357) 
(list 3839.7375 -186.357) 
(list 3839.4375 -196.357) 
(list 3839.4375 -196.357) 
(list 3839.4375 -197.357) 
(list 3765.415 -207.7434) 
(list 3765.415 -212.6864) 
(list 3839.4375 -200.8) 
(list 3839.4375 -201.8) 
(list 3839.4375 -201.8) 
(list 3839.815 -211.8)))
(apply 'command (append '("pline") coords '("c")))
(setq currobj (ssadd (entlast) currobj))
(command "_layer" "set" "prebias" "")
(setq coords (list 
(list 3839.4375 -212.6864) 
(list 3839.4375 -200.8) 
(list 3765.415 -212.6864) 
(list 3765.415 -207.7434) 
(list 3839.4375 -197.357) 
(list 3839.4375 -186.357) 
(list 3840.5625 -186.357) 
(list 3840.5625 -197.357) 
(list 3914.585 -207.7434) 
(list 3914.585 -212.6864) 
(list 3840.5625 -200.8) 
(list 3840.5625 -212.6864)))
(apply 'command (append '("pline") coords '("c")))
(setq currobj (ssadd (entlast) currobj))
(command "_layer" "set" "nitride" "")
(command "_layer" "set" "fda1" "")
(setq coords (list 
(list 3840.5625 -200.657) 
(list 3914.585 -212.5434) 
(list 3914.585 -212.3664) 
(list 3840.5625 -200.58)))
(apply 'command (append '("pline") coords '("c")))
(setq currobj (ssadd (entlast) currobj))
(setq coords (list 
(list 3840.5625 -200.437) 
(list 3914.585 -212.2234) 
(list 3914.585 -212.0464) 
(list 3840.5625 -200.36)))
(apply 'command (append '("pline") coords '("c")))
(setq currobj (ssadd (entlast) currobj))
(setq coords (list 
(list 3840.5625 -200.217) 
(list 3914.585 -211.9034) 
(list 3914.585 -211.7264) 
(list 3840.5625 -200.14)))
(apply 'command (append '("pline") coords '("c")))
(setq currobj (ssadd (entlast) currobj))
(setq coords (list 
(list 3840.5625 -199.997) 
(list 3914.585 -211.5834) 
(list 3914.585 -211.4064) 
(list 3840.5625 -199.92)))
(apply 'command (append '("pline") coords '("c")))
(setq currobj (ssadd (entlast) currobj))
(setq coords (list 
(list 3840.5625 -199.777) 
(list 3914.585 -211.2634) 
(list 3914.585 -211.0864) 
(list 3840.5625 -199.7)))
(apply 'command (append '("pline") coords '("c")))
(setq currobj (ssadd (entlast) currobj))
(setq coords (list 
(list 3840.5625 -199.557) 
(list 3914.585 -210.9434) 
(list 3914.585 -210.7664) 
(list 3840.5625 -199.48)))
(apply 'command (append '("pline") coords '("c")))
(setq currobj (ssadd (entlast) currobj))
(setq coords (list 
(list 3840.5625 -199.337) 
(list 3914.585 -210.6234) 
(list 3914.585 -210.4464) 
(list 3840.5625 -199.26)))
(apply 'command (append '("pline") coords '("c")))
(setq currobj (ssadd (entlast) currobj))
(setq coords (list 
(list 3840.5625 -199.117) 
(list 3914.585 -210.3034) 
(list 3914.585 -210.1264) 
(list 3840.5625 -199.04)))
(apply 'command (append '("pline") coords '("c")))
(setq currobj (ssadd (entlast) currobj))
(setq coords (list 
(list 3840.5625 -198.897) 
(list 3914.585 -209.9834) 
(list 3914.585 -209.8064) 
(list 3840.5625 -198.82)))
(apply 'command (append '("pline") coords '("c")))
(setq currobj (ssadd (entlast) currobj))
(setq coords (list 
(list 3840.5625 -198.677) 
(list 3914.585 -209.6634) 
(list 3914.585 -209.4864) 
(list 3840.5625 -198.6)))
(apply 'command (append '("pline") coords '("c")))
(setq currobj (ssadd (entlast) currobj))
(setq coords (list 
(list 3840.5625 -198.457) 
(list 3914.585 -209.3434) 
(list 3914.585 -209.1664) 
(list 3840.5625 -198.38)))
(apply 'command (append '("pline") coords '("c")))
(setq currobj (ssadd (entlast) currobj))
(setq coords (list 
(list 3840.5625 -198.237) 
(list 3914.585 -209.0234) 
(list 3914.585 -208.8464) 
(list 3840.5625 -198.16)))
(apply 'command (append '("pline") coords '("c")))
(setq currobj (ssadd (entlast) currobj))
(setq coords (list 
(list 3840.5625 -198.017) 
(list 3914.585 -208.7034) 
(list 3914.585 -208.5264) 
(list 3840.5625 -197.94)))
(apply 'command (append '("pline") coords '("c")))
(setq currobj (ssadd (entlast) currobj))
(setq coords (list 
(list 3840.5625 -197.797) 
(list 3914.585 -208.3834) 
(list 3914.585 -208.2064) 
(list 3840.5625 -197.72)))
(apply 'command (append '("pline") coords '("c")))
(setq currobj (ssadd (entlast) currobj))
(setq coords (list 
(list 3840.5625 -197.577) 
(list 3914.585 -208.0634) 
(list 3914.585 -207.8864) 
(list 3840.5625 -197.5)))
(apply 'command (append '("pline") coords '("c")))
(setq currobj (ssadd (entlast) currobj))
(setq coords (list 
(list 3839.4375 -197.5) 
(list 3765.415 -207.8864) 
(list 3765.415 -208.0634) 
(list 3839.4375 -197.577)))
(apply 'command (append '("pline") coords '("c")))
(setq currobj (ssadd (entlast) currobj))
(setq coords (list 
(list 3839.4375 -197.72) 
(list 3765.415 -208.2064) 
(list 3765.415 -208.3834) 
(list 3839.4375 -197.797)))
(apply 'command (append '("pline") coords '("c")))
(setq currobj (ssadd (entlast) currobj))
(setq coords (list 
(list 3839.4375 -197.94) 
(list 3765.415 -208.5264) 
(list 3765.415 -208.7034) 
(list 3839.4375 -198.017)))
(apply 'command (append '("pline") coords '("c")))
(setq currobj (ssadd (entlast) currobj))
(setq coords (list 
(list 3839.4375 -198.16) 
(list 3765.415 -208.8464) 
(list 3765.415 -209.0234) 
(list 3839.4375 -198.237)))
(apply 'command (append '("pline") coords '("c")))
(setq currobj (ssadd (entlast) currobj))
(setq coords (list 
(list 3839.4375 -198.38) 
(list 3765.415 -209.1664) 
(list 3765.415 -209.3434) 
(list 3839.4375 -198.457)))
(apply 'command (append '("pline") coords '("c")))
(setq currobj (ssadd (entlast) currobj))
(setq coords (list 
(list 3839.4375 -198.6) 
(list 3765.415 -209.4864) 
(list 3765.415 -209.6634) 
(list 3839.4375 -198.677)))
(apply 'command (append '("pline") coords '("c")))
(setq currobj (ssadd (entlast) currobj))
(setq coords (list 
(list 3839.4375 -198.82) 
(list 3765.415 -209.8064) 
(list 3765.415 -209.9834) 
(list 3839.4375 -198.897)))
(apply 'command (append '("pline") coords '("c")))
(setq currobj (ssadd (entlast) currobj))
(setq coords (list 
(list 3839.4375 -199.04) 
(list 3765.415 -210.1264) 
(list 3765.415 -210.3034) 
(list 3839.4375 -199.117)))
(apply 'command (append '("pline") coords '("c")))
(setq currobj (ssadd (entlast) currobj))
(setq coords (list 
(list 3839.4375 -199.26) 
(list 3765.415 -210.4464) 
(list 3765.415 -210.6234) 
(list 3839.4375 -199.337)))
(apply 'command (append '("pline") coords '("c")))
(setq currobj (ssadd (entlast) currobj))
(setq coords (list 
(list 3839.4375 -199.48) 
(list 3765.415 -210.7664) 
(list 3765.415 -210.9434) 
(list 3839.4375 -199.557)))
(apply 'command (append '("pline") coords '("c")))
(setq currobj (ssadd (entlast) currobj))
(setq coords (list 
(list 3839.4375 -199.7) 
(list 3765.415 -211.0864) 
(list 3765.415 -211.2634) 
(list 3839.4375 -199.777)))
(apply 'command (append '("pline") coords '("c")))
(setq currobj (ssadd (entlast) currobj))
(setq coords (list 
(list 3839.4375 -199.92) 
(list 3765.415 -211.4064) 
(list 3765.415 -211.5834) 
(list 3839.4375 -199.997)))
(apply 'command (append '("pline") coords '("c")))
(setq currobj (ssadd (entlast) currobj))
(setq coords (list 
(list 3839.4375 -200.14) 
(list 3765.415 -211.7264) 
(list 3765.415 -211.9034) 
(list 3839.4375 -200.217)))
(apply 'command (append '("pline") coords '("c")))
(setq currobj (ssadd (entlast) currobj))
(setq coords (list 
(list 3839.4375 -200.36) 
(list 3765.415 -212.0464) 
(list 3765.415 -212.2234) 
(list 3839.4375 -200.437)))
(apply 'command (append '("pline") coords '("c")))
(setq currobj (ssadd (entlast) currobj))
(setq coords (list 
(list 3839.4375 -200.58) 
(list 3765.415 -212.3664) 
(list 3765.415 -212.5434) 
(list 3839.4375 -200.657)))
(apply 'command (append '("pline") coords '("c")))
(setq currobj (ssadd (entlast) currobj))
(command "_layer" "set" "nitride" "")
(command "_layer" "set" "text" "")
(command "_circle" "3838.985,-211.8" "0.075")
(command "_circle" "3838.985,-211.5" "0.075")
(command "_circle" "3838.985,-211.2" "0.075")
(command "_circle" "3838.985,-210.9" "0.075")
(command "_circle" "3838.985,-210.6" "0.075")
(command "_circle" "3838.685,-211.8" "0.075")
(command "_circle" "3838.685,-211.5" "0.075")
(command "_circle" "3838.685,-211.2" "0.075")
(command "_circle" "3838.685,-210.9" "0.075")
(command "_circle" "3838.685,-210.6" "0.075")
(command "_circle" "3838.385,-211.8" "0.075")
(command "_circle" "3838.385,-211.5" "0.075")
(command "_circle" "3838.385,-211.2" "0.075")
(command "_circle" "3838.385,-210.9" "0.075")
(command "_circle" "3838.385,-210.6" "0.075")
(command "_circle" "3838.085,-211.8" "0.075")
(command "_circle" "3838.085,-211.5" "0.075")
(command "_circle" "3838.085,-211.2" "0.075")
(command "_circle" "3838.085,-210.9" "0.075")
(command "_circle" "3838.085,-210.6" "0.075")
(command "_circle" "3837.785,-211.8" "0.075")
(command "_circle" "3837.785,-211.5" "0.075")
(command "_circle" "3837.785,-211.2" "0.075")
(command "_circle" "3837.785,-210.9" "0.075")
(command "_circle" "3837.785,-210.6" "0.075")
(command "_layer" "set" "nitride" "")
(setq anglednodearray12 currobj)
(setq currobj nil)
(setq currobj (ssadd))
; DRAWING COOLED SINGLE NANOBEAM
(setq coords (list 
(list 3840.2625 -186.357) 
(list 3840.2625 -181.357) 
(list 3839.7375 -181.357) 
(list 3839.7375 -186.357)))
(apply 'command (append '("pline") coords '("c")))
(setq currobj (ssadd (entlast) currobj))
(command "_layer" "set" "prebias" "")
(command "_rectangle" "3839.7375,-186.357" "3840.2625,-181.357")
(setq currobj (ssadd (entlast) currobj))
(command "_layer" "set" "nitride" "")
(setq coords (list 
(list 3840.2625 -181.357) 
(list 3840.5625 -171.357) 
(list 3840.5625 -171.357) 
(list 3840.5625 -170.357) 
(list 3914.585 -171.107) 
(list 3914.585 -166.164) 
(list 3840.5625 -166.914) 
(list 3840.5625 -165.914) 
(list 3840.5625 -165.914) 
(list 3840.2625 -155.914) 
(list 3839.7375 -155.914) 
(list 3839.4375 -165.914) 
(list 3839.4375 -165.914) 
(list 3839.4375 -166.914) 
(list 3765.415 -166.164) 
(list 3765.415 -171.107) 
(list 3839.4375 -170.357) 
(list 3839.4375 -171.357) 
(list 3839.4375 -171.357) 
(list 3839.7375 -181.357)))
(apply 'command (append '("pline") coords '("c")))
(setq currobj (ssadd (entlast) currobj))
(command "_layer" "set" "prebias" "")
(setq coords (list 
(list 3839.4375 -181.357) 
(list 3839.4375 -170.357) 
(list 3765.415 -171.107) 
(list 3765.415 -166.164) 
(list 3839.4375 -166.914) 
(list 3839.4375 -155.914) 
(list 3840.5625 -155.914) 
(list 3840.5625 -166.914) 
(list 3914.585 -166.164) 
(list 3914.585 -171.107) 
(list 3840.5625 -170.357) 
(list 3840.5625 -181.357)))
(apply 'command (append '("pline") coords '("c")))
(setq currobj (ssadd (entlast) currobj))
(command "_layer" "set" "nitride" "")
(command "_layer" "set" "fda1" "")
(setq coords (list 
(list 3840.5625 -170.214) 
(list 3914.585 -170.964) 
(list 3914.585 -170.787) 
(list 3840.5625 -170.137)))
(apply 'command (append '("pline") coords '("c")))
(setq currobj (ssadd (entlast) currobj))
(setq coords (list 
(list 3840.5625 -169.994) 
(list 3914.585 -170.644) 
(list 3914.585 -170.467) 
(list 3840.5625 -169.917)))
(apply 'command (append '("pline") coords '("c")))
(setq currobj (ssadd (entlast) currobj))
(setq coords (list 
(list 3840.5625 -169.774) 
(list 3914.585 -170.324) 
(list 3914.585 -170.147) 
(list 3840.5625 -169.697)))
(apply 'command (append '("pline") coords '("c")))
(setq currobj (ssadd (entlast) currobj))
(setq coords (list 
(list 3840.5625 -169.554) 
(list 3914.585 -170.004) 
(list 3914.585 -169.827) 
(list 3840.5625 -169.477)))
(apply 'command (append '("pline") coords '("c")))
(setq currobj (ssadd (entlast) currobj))
(setq coords (list 
(list 3840.5625 -169.334) 
(list 3914.585 -169.684) 
(list 3914.585 -169.507) 
(list 3840.5625 -169.257)))
(apply 'command (append '("pline") coords '("c")))
(setq currobj (ssadd (entlast) currobj))
(setq coords (list 
(list 3840.5625 -169.114) 
(list 3914.585 -169.364) 
(list 3914.585 -169.187) 
(list 3840.5625 -169.037)))
(apply 'command (append '("pline") coords '("c")))
(setq currobj (ssadd (entlast) currobj))
(setq coords (list 
(list 3840.5625 -168.894) 
(list 3914.585 -169.044) 
(list 3914.585 -168.867) 
(list 3840.5625 -168.817)))
(apply 'command (append '("pline") coords '("c")))
(setq currobj (ssadd (entlast) currobj))
(setq coords (list 
(list 3840.5625 -168.674) 
(list 3914.585 -168.724) 
(list 3914.585 -168.547) 
(list 3840.5625 -168.597)))
(apply 'command (append '("pline") coords '("c")))
(setq currobj (ssadd (entlast) currobj))
(setq coords (list 
(list 3840.5625 -168.454) 
(list 3914.585 -168.404) 
(list 3914.585 -168.227) 
(list 3840.5625 -168.377)))
(apply 'command (append '("pline") coords '("c")))
(setq currobj (ssadd (entlast) currobj))
(setq coords (list 
(list 3840.5625 -168.234) 
(list 3914.585 -168.084) 
(list 3914.585 -167.907) 
(list 3840.5625 -168.157)))
(apply 'command (append '("pline") coords '("c")))
(setq currobj (ssadd (entlast) currobj))
(setq coords (list 
(list 3840.5625 -168.014) 
(list 3914.585 -167.764) 
(list 3914.585 -167.587) 
(list 3840.5625 -167.937)))
(apply 'command (append '("pline") coords '("c")))
(setq currobj (ssadd (entlast) currobj))
(setq coords (list 
(list 3840.5625 -167.794) 
(list 3914.585 -167.444) 
(list 3914.585 -167.267) 
(list 3840.5625 -167.717)))
(apply 'command (append '("pline") coords '("c")))
(setq currobj (ssadd (entlast) currobj))
(setq coords (list 
(list 3840.5625 -167.574) 
(list 3914.585 -167.124) 
(list 3914.585 -166.947) 
(list 3840.5625 -167.497)))
(apply 'command (append '("pline") coords '("c")))
(setq currobj (ssadd (entlast) currobj))
(setq coords (list 
(list 3840.5625 -167.354) 
(list 3914.585 -166.804) 
(list 3914.585 -166.627) 
(list 3840.5625 -167.277)))
(apply 'command (append '("pline") coords '("c")))
(setq currobj (ssadd (entlast) currobj))
(setq coords (list 
(list 3840.5625 -167.134) 
(list 3914.585 -166.484) 
(list 3914.585 -166.307) 
(list 3840.5625 -167.057)))
(apply 'command (append '("pline") coords '("c")))
(setq currobj (ssadd (entlast) currobj))
(setq coords (list 
(list 3839.4375 -167.057) 
(list 3765.415 -166.307) 
(list 3765.415 -166.484) 
(list 3839.4375 -167.134)))
(apply 'command (append '("pline") coords '("c")))
(setq currobj (ssadd (entlast) currobj))
(setq coords (list 
(list 3839.4375 -167.277) 
(list 3765.415 -166.627) 
(list 3765.415 -166.804) 
(list 3839.4375 -167.354)))
(apply 'command (append '("pline") coords '("c")))
(setq currobj (ssadd (entlast) currobj))
(setq coords (list 
(list 3839.4375 -167.497) 
(list 3765.415 -166.947) 
(list 3765.415 -167.124) 
(list 3839.4375 -167.574)))
(apply 'command (append '("pline") coords '("c")))
(setq currobj (ssadd (entlast) currobj))
(setq coords (list 
(list 3839.4375 -167.717) 
(list 3765.415 -167.267) 
(list 3765.415 -167.444) 
(list 3839.4375 -167.794)))
(apply 'command (append '("pline") coords '("c")))
(setq currobj (ssadd (entlast) currobj))
(setq coords (list 
(list 3839.4375 -167.937) 
(list 3765.415 -167.587) 
(list 3765.415 -167.764) 
(list 3839.4375 -168.014)))
(apply 'command (append '("pline") coords '("c")))
(setq currobj (ssadd (entlast) currobj))
(setq coords (list 
(list 3839.4375 -168.157) 
(list 3765.415 -167.907) 
(list 3765.415 -168.084) 
(list 3839.4375 -168.234)))
(apply 'command (append '("pline") coords '("c")))
(setq currobj (ssadd (entlast) currobj))
(setq coords (list 
(list 3839.4375 -168.377) 
(list 3765.415 -168.227) 
(list 3765.415 -168.404) 
(list 3839.4375 -168.454)))
(apply 'command (append '("pline") coords '("c")))
(setq currobj (ssadd (entlast) currobj))
(setq coords (list 
(list 3839.4375 -168.597) 
(list 3765.415 -168.547) 
(list 3765.415 -168.724) 
(list 3839.4375 -168.674)))
(apply 'command (append '("pline") coords '("c")))
(setq currobj (ssadd (entlast) currobj))
(setq coords (list 
(list 3839.4375 -168.817) 
(list 3765.415 -168.867) 
(list 3765.415 -169.044) 
(list 3839.4375 -168.894)))
(apply 'command (append '("pline") coords '("c")))
(setq currobj (ssadd (entlast) currobj))
(setq coords (list 
(list 3839.4375 -169.037) 
(list 3765.415 -169.187) 
(list 3765.415 -169.364) 
(list 3839.4375 -169.114)))
(apply 'command (append '("pline") coords '("c")))
(setq currobj (ssadd (entlast) currobj))
(setq coords (list 
(list 3839.4375 -169.257) 
(list 3765.415 -169.507) 
(list 3765.415 -169.684) 
(list 3839.4375 -169.334)))
(apply 'command (append '("pline") coords '("c")))
(setq currobj (ssadd (entlast) currobj))
(setq coords (list 
(list 3839.4375 -169.477) 
(list 3765.415 -169.827) 
(list 3765.415 -170.004) 
(list 3839.4375 -169.554)))
(apply 'command (append '("pline") coords '("c")))
(setq currobj (ssadd (entlast) currobj))
(setq coords (list 
(list 3839.4375 -169.697) 
(list 3765.415 -170.147) 
(list 3765.415 -170.324) 
(list 3839.4375 -169.774)))
(apply 'command (append '("pline") coords '("c")))
(setq currobj (ssadd (entlast) currobj))
(setq coords (list 
(list 3839.4375 -169.917) 
(list 3765.415 -170.467) 
(list 3765.415 -170.644) 
(list 3839.4375 -169.994)))
(apply 'command (append '("pline") coords '("c")))
(setq currobj (ssadd (entlast) currobj))
(setq coords (list 
(list 3839.4375 -170.137) 
(list 3765.415 -170.787) 
(list 3765.415 -170.964) 
(list 3839.4375 -170.214)))
(apply 'command (append '("pline") coords '("c")))
(setq currobj (ssadd (entlast) currobj))
(command "_layer" "set" "nitride" "")
(command "_layer" "set" "text" "")
(command "_circle" "3839.0625,-181.357" "0.075")
(command "_circle" "3839.0625,-181.057" "0.075")
(command "_circle" "3839.0625,-180.757" "0.075")
(command "_circle" "3839.0625,-180.457" "0.075")
(command "_circle" "3839.0625,-180.157" "0.075")
(command "_circle" "3838.7625,-181.357" "0.075")
(command "_circle" "3838.7625,-181.057" "0.075")
(command "_circle" "3838.7625,-180.757" "0.075")
(command "_circle" "3838.7625,-180.457" "0.075")
(command "_circle" "3838.7625,-180.157" "0.075")
(command "_circle" "3838.4625,-181.357" "0.075")
(command "_circle" "3838.4625,-181.057" "0.075")
(command "_circle" "3838.4625,-180.757" "0.075")
(command "_circle" "3838.4625,-180.457" "0.075")
(command "_circle" "3838.4625,-180.157" "0.075")
(command "_circle" "3838.1625,-181.357" "0.075")
(command "_circle" "3838.1625,-181.057" "0.075")
(command "_circle" "3838.1625,-180.757" "0.075")
(command "_circle" "3838.1625,-180.457" "0.075")
(command "_circle" "3838.1625,-180.157" "0.075")
(command "_circle" "3837.8625,-181.357" "0.075")
(command "_circle" "3837.8625,-181.057" "0.075")
(command "_circle" "3837.8625,-180.757" "0.075")
(command "_circle" "3837.8625,-180.457" "0.075")
(command "_circle" "3837.8625,-180.157" "0.075")
(command "_layer" "set" "nitride" "")
(setq coords (list 
(list 3840.2625 -155.914) 
(list 3840.2625 -40.2693) 
(list 3839.7375 -40.2693) 
(list 3839.7375 -155.914)))
(apply 'command (append '("pline") coords '("c")))
(setq currobj (ssadd (entlast) currobj))
(command "_layer" "set" "prebias" "")
(command "_rectangle" "3839.7375,-155.914" "3840.2625,-40.2693")
(setq currobj (ssadd (entlast) currobj))
(command "_layer" "set" "nitride" "")
(setq coords (list 
(list 3840.2625 -40.2693) 
(list 3840.5625 -30.2693) 
(list 3840.5625 -30.2693) 
(list 3840.5625 -29.2693) 
(list 3914.585 -30.0193) 
(list 3914.585 -25.0763) 
(list 3840.5625 -25.8263) 
(list 3840.5625 -24.8263) 
(list 3840.5625 -24.8263) 
(list 3840.2625 -14.8263) 
(list 3839.7375 -14.8263) 
(list 3839.4375 -24.8263) 
(list 3839.4375 -24.8263) 
(list 3839.4375 -25.8263) 
(list 3765.415 -25.0763) 
(list 3765.415 -30.0193) 
(list 3839.4375 -29.2693) 
(list 3839.4375 -30.2693) 
(list 3839.4375 -30.2693) 
(list 3839.7375 -40.2693)))
(apply 'command (append '("pline") coords '("c")))
(setq currobj (ssadd (entlast) currobj))
(command "_layer" "set" "prebias" "")
(setq coords (list 
(list 3839.4375 -40.2693) 
(list 3839.4375 -29.2693) 
(list 3765.415 -30.0193) 
(list 3765.415 -25.0763) 
(list 3839.4375 -25.8263) 
(list 3839.4375 -14.8263) 
(list 3840.5625 -14.8263) 
(list 3840.5625 -25.8263) 
(list 3914.585 -25.0763) 
(list 3914.585 -30.0193) 
(list 3840.5625 -29.2693) 
(list 3840.5625 -40.2693)))
(apply 'command (append '("pline") coords '("c")))
(setq currobj (ssadd (entlast) currobj))
(command "_layer" "set" "nitride" "")
(command "_layer" "set" "fda1" "")
(setq coords (list 
(list 3840.5625 -29.1263) 
(list 3914.585 -29.8763) 
(list 3914.585 -29.6993) 
(list 3840.5625 -29.0493)))
(apply 'command (append '("pline") coords '("c")))
(setq currobj (ssadd (entlast) currobj))
(setq coords (list 
(list 3840.5625 -28.9063) 
(list 3914.585 -29.5563) 
(list 3914.585 -29.3793) 
(list 3840.5625 -28.8293)))
(apply 'command (append '("pline") coords '("c")))
(setq currobj (ssadd (entlast) currobj))
(setq coords (list 
(list 3840.5625 -28.6863) 
(list 3914.585 -29.2363) 
(list 3914.585 -29.0593) 
(list 3840.5625 -28.6093)))
(apply 'command (append '("pline") coords '("c")))
(setq currobj (ssadd (entlast) currobj))
(setq coords (list 
(list 3840.5625 -28.4663) 
(list 3914.585 -28.9163) 
(list 3914.585 -28.7393) 
(list 3840.5625 -28.3893)))
(apply 'command (append '("pline") coords '("c")))
(setq currobj (ssadd (entlast) currobj))
(setq coords (list 
(list 3840.5625 -28.2463) 
(list 3914.585 -28.5963) 
(list 3914.585 -28.4193) 
(list 3840.5625 -28.1693)))
(apply 'command (append '("pline") coords '("c")))
(setq currobj (ssadd (entlast) currobj))
(setq coords (list 
(list 3840.5625 -28.0263) 
(list 3914.585 -28.2763) 
(list 3914.585 -28.0993) 
(list 3840.5625 -27.9493)))
(apply 'command (append '("pline") coords '("c")))
(setq currobj (ssadd (entlast) currobj))
(setq coords (list 
(list 3840.5625 -27.8063) 
(list 3914.585 -27.9563) 
(list 3914.585 -27.7793) 
(list 3840.5625 -27.7293)))
(apply 'command (append '("pline") coords '("c")))
(setq currobj (ssadd (entlast) currobj))
(setq coords (list 
(list 3840.5625 -27.5863) 
(list 3914.585 -27.6363) 
(list 3914.585 -27.4593) 
(list 3840.5625 -27.5093)))
(apply 'command (append '("pline") coords '("c")))
(setq currobj (ssadd (entlast) currobj))
(setq coords (list 
(list 3840.5625 -27.3663) 
(list 3914.585 -27.3163) 
(list 3914.585 -27.1393) 
(list 3840.5625 -27.2893)))
(apply 'command (append '("pline") coords '("c")))
(setq currobj (ssadd (entlast) currobj))
(setq coords (list 
(list 3840.5625 -27.1463) 
(list 3914.585 -26.9963) 
(list 3914.585 -26.8193) 
(list 3840.5625 -27.0693)))
(apply 'command (append '("pline") coords '("c")))
(setq currobj (ssadd (entlast) currobj))
(setq coords (list 
(list 3840.5625 -26.9263) 
(list 3914.585 -26.6763) 
(list 3914.585 -26.4993) 
(list 3840.5625 -26.8493)))
(apply 'command (append '("pline") coords '("c")))
(setq currobj (ssadd (entlast) currobj))
(setq coords (list 
(list 3840.5625 -26.7063) 
(list 3914.585 -26.3563) 
(list 3914.585 -26.1793) 
(list 3840.5625 -26.6293)))
(apply 'command (append '("pline") coords '("c")))
(setq currobj (ssadd (entlast) currobj))
(setq coords (list 
(list 3840.5625 -26.4863) 
(list 3914.585 -26.0363) 
(list 3914.585 -25.8593) 
(list 3840.5625 -26.4093)))
(apply 'command (append '("pline") coords '("c")))
(setq currobj (ssadd (entlast) currobj))
(setq coords (list 
(list 3840.5625 -26.2663) 
(list 3914.585 -25.7163) 
(list 3914.585 -25.5393) 
(list 3840.5625 -26.1893)))
(apply 'command (append '("pline") coords '("c")))
(setq currobj (ssadd (entlast) currobj))
(setq coords (list 
(list 3840.5625 -26.0463) 
(list 3914.585 -25.3963) 
(list 3914.585 -25.2193) 
(list 3840.5625 -25.9693)))
(apply 'command (append '("pline") coords '("c")))
(setq currobj (ssadd (entlast) currobj))
(setq coords (list 
(list 3839.4375 -25.9693) 
(list 3765.415 -25.2193) 
(list 3765.415 -25.3963) 
(list 3839.4375 -26.0463)))
(apply 'command (append '("pline") coords '("c")))
(setq currobj (ssadd (entlast) currobj))
(setq coords (list 
(list 3839.4375 -26.1893) 
(list 3765.415 -25.5393) 
(list 3765.415 -25.7163) 
(list 3839.4375 -26.2663)))
(apply 'command (append '("pline") coords '("c")))
(setq currobj (ssadd (entlast) currobj))
(setq coords (list 
(list 3839.4375 -26.4093) 
(list 3765.415 -25.8593) 
(list 3765.415 -26.0363) 
(list 3839.4375 -26.4863)))
(apply 'command (append '("pline") coords '("c")))
(setq currobj (ssadd (entlast) currobj))
(setq coords (list 
(list 3839.4375 -26.6293) 
(list 3765.415 -26.1793) 
(list 3765.415 -26.3563) 
(list 3839.4375 -26.7063)))
(apply 'command (append '("pline") coords '("c")))
(setq currobj (ssadd (entlast) currobj))
(setq coords (list 
(list 3839.4375 -26.8493) 
(list 3765.415 -26.4993) 
(list 3765.415 -26.6763) 
(list 3839.4375 -26.9263)))
(apply 'command (append '("pline") coords '("c")))
(setq currobj (ssadd (entlast) currobj))
(setq coords (list 
(list 3839.4375 -27.0693) 
(list 3765.415 -26.8193) 
(list 3765.415 -26.9963) 
(list 3839.4375 -27.1463)))
(apply 'command (append '("pline") coords '("c")))
(setq currobj (ssadd (entlast) currobj))
(setq coords (list 
(list 3839.4375 -27.2893) 
(list 3765.415 -27.1393) 
(list 3765.415 -27.3163) 
(list 3839.4375 -27.3663)))
(apply 'command (append '("pline") coords '("c")))
(setq currobj (ssadd (entlast) currobj))
(setq coords (list 
(list 3839.4375 -27.5093) 
(list 3765.415 -27.4593) 
(list 3765.415 -27.6363) 
(list 3839.4375 -27.5863)))
(apply 'command (append '("pline") coords '("c")))
(setq currobj (ssadd (entlast) currobj))
(setq coords (list 
(list 3839.4375 -27.7293) 
(list 3765.415 -27.7793) 
(list 3765.415 -27.9563) 
(list 3839.4375 -27.8063)))
(apply 'command (append '("pline") coords '("c")))
(setq currobj (ssadd (entlast) currobj))
(setq coords (list 
(list 3839.4375 -27.9493) 
(list 3765.415 -28.0993) 
(list 3765.415 -28.2763) 
(list 3839.4375 -28.0263)))
(apply 'command (append '("pline") coords '("c")))
(setq currobj (ssadd (entlast) currobj))
(setq coords (list 
(list 3839.4375 -28.1693) 
(list 3765.415 -28.4193) 
(list 3765.415 -28.5963) 
(list 3839.4375 -28.2463)))
(apply 'command (append '("pline") coords '("c")))
(setq currobj (ssadd (entlast) currobj))
(setq coords (list 
(list 3839.4375 -28.3893) 
(list 3765.415 -28.7393) 
(list 3765.415 -28.9163) 
(list 3839.4375 -28.4663)))
(apply 'command (append '("pline") coords '("c")))
(setq currobj (ssadd (entlast) currobj))
(setq coords (list 
(list 3839.4375 -28.6093) 
(list 3765.415 -29.0593) 
(list 3765.415 -29.2363) 
(list 3839.4375 -28.6863)))
(apply 'command (append '("pline") coords '("c")))
(setq currobj (ssadd (entlast) currobj))
(setq coords (list 
(list 3839.4375 -28.8293) 
(list 3765.415 -29.3793) 
(list 3765.415 -29.5563) 
(list 3839.4375 -28.9063)))
(apply 'command (append '("pline") coords '("c")))
(setq currobj (ssadd (entlast) currobj))
(setq coords (list 
(list 3839.4375 -29.0493) 
(list 3765.415 -29.6993) 
(list 3765.415 -29.8763) 
(list 3839.4375 -29.1263)))
(apply 'command (append '("pline") coords '("c")))
(setq currobj (ssadd (entlast) currobj))
(command "_layer" "set" "nitride" "")
(command "_layer" "set" "text" "")
(command "_circle" "3839.0625,-40.2693" "0.075")
(command "_circle" "3839.0625,-39.9693" "0.075")
(command "_circle" "3839.0625,-39.6693" "0.075")
(command "_circle" "3839.0625,-39.3693" "0.075")
(command "_circle" "3839.0625,-39.0693" "0.075")
(command "_circle" "3838.7625,-40.2693" "0.075")
(command "_circle" "3838.7625,-39.9693" "0.075")
(command "_circle" "3838.7625,-39.6693" "0.075")
(command "_circle" "3838.7625,-39.3693" "0.075")
(command "_circle" "3838.7625,-39.0693" "0.075")
(command "_circle" "3838.4625,-40.2693" "0.075")
(command "_circle" "3838.4625,-39.9693" "0.075")
(command "_circle" "3838.4625,-39.6693" "0.075")
(command "_circle" "3838.4625,-39.3693" "0.075")
(command "_circle" "3838.4625,-39.0693" "0.075")
(command "_circle" "3838.1625,-40.2693" "0.075")
(command "_circle" "3838.1625,-39.9693" "0.075")
(command "_circle" "3838.1625,-39.6693" "0.075")
(command "_circle" "3838.1625,-39.3693" "0.075")
(command "_circle" "3838.1625,-39.0693" "0.075")
(command "_circle" "3837.8625,-40.2693" "0.075")
(command "_circle" "3837.8625,-39.9693" "0.075")
(command "_circle" "3837.8625,-39.6693" "0.075")
(command "_circle" "3837.8625,-39.3693" "0.075")
(command "_circle" "3837.8625,-39.0693" "0.075")
(command "_layer" "set" "nitride" "")
(setq coords (list 
(list 3840.2625 -14.8263) 
(list 3840.2625 100.8184) 
(list 3839.7375 100.8184) 
(list 3839.7375 -14.8263)))
(apply 'command (append '("pline") coords '("c")))
(setq currobj (ssadd (entlast) currobj))
(command "_layer" "set" "prebias" "")
(command "_rectangle" "3839.7375,-14.8263" "3840.2625,100.8184")
(setq currobj (ssadd (entlast) currobj))
(command "_layer" "set" "nitride" "")
(setq coords (list 
(list 3840.2625 100.8184) 
(list 3840.5625 110.8184) 
(list 3840.5625 110.8184) 
(list 3840.5625 111.8184) 
(list 3914.585 111.0684) 
(list 3914.585 116.0114) 
(list 3840.5625 115.2614) 
(list 3840.5625 116.2614) 
(list 3840.5625 116.2614) 
(list 3840.2625 126.2614) 
(list 3839.7375 126.2614) 
(list 3839.4375 116.2614) 
(list 3839.4375 116.2614) 
(list 3839.4375 115.2614) 
(list 3765.415 116.0114) 
(list 3765.415 111.0684) 
(list 3839.4375 111.8184) 
(list 3839.4375 110.8184) 
(list 3839.4375 110.8184) 
(list 3839.7375 100.8184)))
(apply 'command (append '("pline") coords '("c")))
(setq currobj (ssadd (entlast) currobj))
(command "_layer" "set" "prebias" "")
(setq coords (list 
(list 3839.4375 100.8184) 
(list 3839.4375 111.8184) 
(list 3765.415 111.0684) 
(list 3765.415 116.0114) 
(list 3839.4375 115.2614) 
(list 3839.4375 126.2614) 
(list 3840.5625 126.2614) 
(list 3840.5625 115.2614) 
(list 3914.585 116.0114) 
(list 3914.585 111.0684) 
(list 3840.5625 111.8184) 
(list 3840.5625 100.8184)))
(apply 'command (append '("pline") coords '("c")))
(setq currobj (ssadd (entlast) currobj))
(command "_layer" "set" "nitride" "")
(command "_layer" "set" "fda1" "")
(setq coords (list 
(list 3840.5625 111.9614) 
(list 3914.585 111.2114) 
(list 3914.585 111.3884) 
(list 3840.5625 112.0384)))
(apply 'command (append '("pline") coords '("c")))
(setq currobj (ssadd (entlast) currobj))
(setq coords (list 
(list 3840.5625 112.1814) 
(list 3914.585 111.5314) 
(list 3914.585 111.7084) 
(list 3840.5625 112.2584)))
(apply 'command (append '("pline") coords '("c")))
(setq currobj (ssadd (entlast) currobj))
(setq coords (list 
(list 3840.5625 112.4014) 
(list 3914.585 111.8514) 
(list 3914.585 112.0284) 
(list 3840.5625 112.4784)))
(apply 'command (append '("pline") coords '("c")))
(setq currobj (ssadd (entlast) currobj))
(setq coords (list 
(list 3840.5625 112.6214) 
(list 3914.585 112.1714) 
(list 3914.585 112.3484) 
(list 3840.5625 112.6984)))
(apply 'command (append '("pline") coords '("c")))
(setq currobj (ssadd (entlast) currobj))
(setq coords (list 
(list 3840.5625 112.8414) 
(list 3914.585 112.4914) 
(list 3914.585 112.6684) 
(list 3840.5625 112.9184)))
(apply 'command (append '("pline") coords '("c")))
(setq currobj (ssadd (entlast) currobj))
(setq coords (list 
(list 3840.5625 113.0614) 
(list 3914.585 112.8114) 
(list 3914.585 112.9884) 
(list 3840.5625 113.1384)))
(apply 'command (append '("pline") coords '("c")))
(setq currobj (ssadd (entlast) currobj))
(setq coords (list 
(list 3840.5625 113.2814) 
(list 3914.585 113.1314) 
(list 3914.585 113.3084) 
(list 3840.5625 113.3584)))
(apply 'command (append '("pline") coords '("c")))
(setq currobj (ssadd (entlast) currobj))
(setq coords (list 
(list 3840.5625 113.5014) 
(list 3914.585 113.4514) 
(list 3914.585 113.6284) 
(list 3840.5625 113.5784)))
(apply 'command (append '("pline") coords '("c")))
(setq currobj (ssadd (entlast) currobj))
(setq coords (list 
(list 3840.5625 113.7214) 
(list 3914.585 113.7714) 
(list 3914.585 113.9484) 
(list 3840.5625 113.7984)))
(apply 'command (append '("pline") coords '("c")))
(setq currobj (ssadd (entlast) currobj))
(setq coords (list 
(list 3840.5625 113.9414) 
(list 3914.585 114.0914) 
(list 3914.585 114.2684) 
(list 3840.5625 114.0184)))
(apply 'command (append '("pline") coords '("c")))
(setq currobj (ssadd (entlast) currobj))
(setq coords (list 
(list 3840.5625 114.1614) 
(list 3914.585 114.4114) 
(list 3914.585 114.5884) 
(list 3840.5625 114.2384)))
(apply 'command (append '("pline") coords '("c")))
(setq currobj (ssadd (entlast) currobj))
(setq coords (list 
(list 3840.5625 114.3814) 
(list 3914.585 114.7314) 
(list 3914.585 114.9084) 
(list 3840.5625 114.4584)))
(apply 'command (append '("pline") coords '("c")))
(setq currobj (ssadd (entlast) currobj))
(setq coords (list 
(list 3840.5625 114.6014) 
(list 3914.585 115.0514) 
(list 3914.585 115.2284) 
(list 3840.5625 114.6784)))
(apply 'command (append '("pline") coords '("c")))
(setq currobj (ssadd (entlast) currobj))
(setq coords (list 
(list 3840.5625 114.8214) 
(list 3914.585 115.3714) 
(list 3914.585 115.5484) 
(list 3840.5625 114.8984)))
(apply 'command (append '("pline") coords '("c")))
(setq currobj (ssadd (entlast) currobj))
(setq coords (list 
(list 3840.5625 115.0414) 
(list 3914.585 115.6914) 
(list 3914.585 115.8684) 
(list 3840.5625 115.1184)))
(apply 'command (append '("pline") coords '("c")))
(setq currobj (ssadd (entlast) currobj))
(setq coords (list 
(list 3839.4375 115.1184) 
(list 3765.415 115.8684) 
(list 3765.415 115.6914) 
(list 3839.4375 115.0414)))
(apply 'command (append '("pline") coords '("c")))
(setq currobj (ssadd (entlast) currobj))
(setq coords (list 
(list 3839.4375 114.8984) 
(list 3765.415 115.5484) 
(list 3765.415 115.3714) 
(list 3839.4375 114.8214)))
(apply 'command (append '("pline") coords '("c")))
(setq currobj (ssadd (entlast) currobj))
(setq coords (list 
(list 3839.4375 114.6784) 
(list 3765.415 115.2284) 
(list 3765.415 115.0514) 
(list 3839.4375 114.6014)))
(apply 'command (append '("pline") coords '("c")))
(setq currobj (ssadd (entlast) currobj))
(setq coords (list 
(list 3839.4375 114.4584) 
(list 3765.415 114.9084) 
(list 3765.415 114.7314) 
(list 3839.4375 114.3814)))
(apply 'command (append '("pline") coords '("c")))
(setq currobj (ssadd (entlast) currobj))
(setq coords (list 
(list 3839.4375 114.2384) 
(list 3765.415 114.5884) 
(list 3765.415 114.4114) 
(list 3839.4375 114.1614)))
(apply 'command (append '("pline") coords '("c")))
(setq currobj (ssadd (entlast) currobj))
(setq coords (list 
(list 3839.4375 114.0184) 
(list 3765.415 114.2684) 
(list 3765.415 114.0914) 
(list 3839.4375 113.9414)))
(apply 'command (append '("pline") coords '("c")))
(setq currobj (ssadd (entlast) currobj))
(setq coords (list 
(list 3839.4375 113.7984) 
(list 3765.415 113.9484) 
(list 3765.415 113.7714) 
(list 3839.4375 113.7214)))
(apply 'command (append '("pline") coords '("c")))
(setq currobj (ssadd (entlast) currobj))
(setq coords (list 
(list 3839.4375 113.5784) 
(list 3765.415 113.6284) 
(list 3765.415 113.4514) 
(list 3839.4375 113.5014)))
(apply 'command (append '("pline") coords '("c")))
(setq currobj (ssadd (entlast) currobj))
(setq coords (list 
(list 3839.4375 113.3584) 
(list 3765.415 113.3084) 
(list 3765.415 113.1314) 
(list 3839.4375 113.2814)))
(apply 'command (append '("pline") coords '("c")))
(setq currobj (ssadd (entlast) currobj))
(setq coords (list 
(list 3839.4375 113.1384) 
(list 3765.415 112.9884) 
(list 3765.415 112.8114) 
(list 3839.4375 113.0614)))
(apply 'command (append '("pline") coords '("c")))
(setq currobj (ssadd (entlast) currobj))
(setq coords (list 
(list 3839.4375 112.9184) 
(list 3765.415 112.6684) 
(list 3765.415 112.4914) 
(list 3839.4375 112.8414)))
(apply 'command (append '("pline") coords '("c")))
(setq currobj (ssadd (entlast) currobj))
(setq coords (list 
(list 3839.4375 112.6984) 
(list 3765.415 112.3484) 
(list 3765.415 112.1714) 
(list 3839.4375 112.6214)))
(apply 'command (append '("pline") coords '("c")))
(setq currobj (ssadd (entlast) currobj))
(setq coords (list 
(list 3839.4375 112.4784) 
(list 3765.415 112.0284) 
(list 3765.415 111.8514) 
(list 3839.4375 112.4014)))
(apply 'command (append '("pline") coords '("c")))
(setq currobj (ssadd (entlast) currobj))
(setq coords (list 
(list 3839.4375 112.2584) 
(list 3765.415 111.7084) 
(list 3765.415 111.5314) 
(list 3839.4375 112.1814)))
(apply 'command (append '("pline") coords '("c")))
(setq currobj (ssadd (entlast) currobj))
(setq coords (list 
(list 3839.4375 112.0384) 
(list 3765.415 111.3884) 
(list 3765.415 111.2114) 
(list 3839.4375 111.9614)))
(apply 'command (append '("pline") coords '("c")))
(setq currobj (ssadd (entlast) currobj))
(command "_layer" "set" "nitride" "")
(command "_layer" "set" "text" "")
(command "_circle" "3839.0625,100.8184" "0.075")
(command "_circle" "3839.0625,101.1184" "0.075")
(command "_circle" "3839.0625,101.4184" "0.075")
(command "_circle" "3839.0625,101.7184" "0.075")
(command "_circle" "3839.0625,102.0184" "0.075")
(command "_circle" "3838.7625,100.8184" "0.075")
(command "_circle" "3838.7625,101.1184" "0.075")
(command "_circle" "3838.7625,101.4184" "0.075")
(command "_circle" "3838.7625,101.7184" "0.075")
(command "_circle" "3838.7625,102.0184" "0.075")
(command "_circle" "3838.4625,100.8184" "0.075")
(command "_circle" "3838.4625,101.1184" "0.075")
(command "_circle" "3838.4625,101.4184" "0.075")
(command "_circle" "3838.4625,101.7184" "0.075")
(command "_circle" "3838.4625,102.0184" "0.075")
(command "_circle" "3838.1625,100.8184" "0.075")
(command "_circle" "3838.1625,101.1184" "0.075")
(command "_circle" "3838.1625,101.4184" "0.075")
(command "_circle" "3838.1625,101.7184" "0.075")
(command "_circle" "3838.1625,102.0184" "0.075")
(command "_circle" "3837.8625,100.8184" "0.075")
(command "_circle" "3837.8625,101.1184" "0.075")
(command "_circle" "3837.8625,101.4184" "0.075")
(command "_circle" "3837.8625,101.7184" "0.075")
(command "_circle" "3837.8625,102.0184" "0.075")
(command "_layer" "set" "nitride" "")
(setq coords (list 
(list 3840.2625 126.2614) 
(list 3840.2625 241.9061) 
(list 3839.7375 241.9061) 
(list 3839.7375 126.2614)))
(apply 'command (append '("pline") coords '("c")))
(setq currobj (ssadd (entlast) currobj))
(command "_layer" "set" "prebias" "")
(command "_rectangle" "3839.7375,126.2614" "3840.2625,241.9061")
(setq currobj (ssadd (entlast) currobj))
(command "_layer" "set" "nitride" "")
(setq coords (list 
(list 3840.2625 241.9061) 
(list 3840.5625 251.9061) 
(list 3840.5625 251.9061) 
(list 3840.5625 252.9061) 
(list 3914.585 252.1561) 
(list 3914.585 257.0991) 
(list 3840.5625 256.3491) 
(list 3840.5625 257.3491) 
(list 3840.5625 257.3491) 
(list 3840.2625 267.3491) 
(list 3839.7375 267.3491) 
(list 3839.4375 257.3491) 
(list 3839.4375 257.3491) 
(list 3839.4375 256.3491) 
(list 3765.415 257.0991) 
(list 3765.415 252.1561) 
(list 3839.4375 252.9061) 
(list 3839.4375 251.9061) 
(list 3839.4375 251.9061) 
(list 3839.7375 241.9061)))
(apply 'command (append '("pline") coords '("c")))
(setq currobj (ssadd (entlast) currobj))
(command "_layer" "set" "prebias" "")
(setq coords (list 
(list 3839.4375 241.9061) 
(list 3839.4375 252.9061) 
(list 3765.415 252.1561) 
(list 3765.415 257.0991) 
(list 3839.4375 256.3491) 
(list 3839.4375 267.3491) 
(list 3840.5625 267.3491) 
(list 3840.5625 256.3491) 
(list 3914.585 257.0991) 
(list 3914.585 252.1561) 
(list 3840.5625 252.9061) 
(list 3840.5625 241.9061)))
(apply 'command (append '("pline") coords '("c")))
(setq currobj (ssadd (entlast) currobj))
(command "_layer" "set" "nitride" "")
(command "_layer" "set" "fda1" "")
(setq coords (list 
(list 3840.5625 253.0491) 
(list 3914.585 252.2991) 
(list 3914.585 252.4761) 
(list 3840.5625 253.1261)))
(apply 'command (append '("pline") coords '("c")))
(setq currobj (ssadd (entlast) currobj))
(setq coords (list 
(list 3840.5625 253.2691) 
(list 3914.585 252.6191) 
(list 3914.585 252.7961) 
(list 3840.5625 253.3461)))
(apply 'command (append '("pline") coords '("c")))
(setq currobj (ssadd (entlast) currobj))
(setq coords (list 
(list 3840.5625 253.4891) 
(list 3914.585 252.9391) 
(list 3914.585 253.1161) 
(list 3840.5625 253.5661)))
(apply 'command (append '("pline") coords '("c")))
(setq currobj (ssadd (entlast) currobj))
(setq coords (list 
(list 3840.5625 253.7091) 
(list 3914.585 253.2591) 
(list 3914.585 253.4361) 
(list 3840.5625 253.7861)))
(apply 'command (append '("pline") coords '("c")))
(setq currobj (ssadd (entlast) currobj))
(setq coords (list 
(list 3840.5625 253.9291) 
(list 3914.585 253.5791) 
(list 3914.585 253.7561) 
(list 3840.5625 254.0061)))
(apply 'command (append '("pline") coords '("c")))
(setq currobj (ssadd (entlast) currobj))
(setq coords (list 
(list 3840.5625 254.1491) 
(list 3914.585 253.8991) 
(list 3914.585 254.0761) 
(list 3840.5625 254.2261)))
(apply 'command (append '("pline") coords '("c")))
(setq currobj (ssadd (entlast) currobj))
(setq coords (list 
(list 3840.5625 254.3691) 
(list 3914.585 254.2191) 
(list 3914.585 254.3961) 
(list 3840.5625 254.4461)))
(apply 'command (append '("pline") coords '("c")))
(setq currobj (ssadd (entlast) currobj))
(setq coords (list 
(list 3840.5625 254.5891) 
(list 3914.585 254.5391) 
(list 3914.585 254.7161) 
(list 3840.5625 254.6661)))
(apply 'command (append '("pline") coords '("c")))
(setq currobj (ssadd (entlast) currobj))
(setq coords (list 
(list 3840.5625 254.8091) 
(list 3914.585 254.8591) 
(list 3914.585 255.0361) 
(list 3840.5625 254.8861)))
(apply 'command (append '("pline") coords '("c")))
(setq currobj (ssadd (entlast) currobj))
(setq coords (list 
(list 3840.5625 255.0291) 
(list 3914.585 255.1791) 
(list 3914.585 255.3561) 
(list 3840.5625 255.1061)))
(apply 'command (append '("pline") coords '("c")))
(setq currobj (ssadd (entlast) currobj))
(setq coords (list 
(list 3840.5625 255.2491) 
(list 3914.585 255.4991) 
(list 3914.585 255.6761) 
(list 3840.5625 255.3261)))
(apply 'command (append '("pline") coords '("c")))
(setq currobj (ssadd (entlast) currobj))
(setq coords (list 
(list 3840.5625 255.4691) 
(list 3914.585 255.8191) 
(list 3914.585 255.9961) 
(list 3840.5625 255.5461)))
(apply 'command (append '("pline") coords '("c")))
(setq currobj (ssadd (entlast) currobj))
(setq coords (list 
(list 3840.5625 255.6891) 
(list 3914.585 256.1391) 
(list 3914.585 256.3161) 
(list 3840.5625 255.7661)))
(apply 'command (append '("pline") coords '("c")))
(setq currobj (ssadd (entlast) currobj))
(setq coords (list 
(list 3840.5625 255.9091) 
(list 3914.585 256.4591) 
(list 3914.585 256.6361) 
(list 3840.5625 255.9861)))
(apply 'command (append '("pline") coords '("c")))
(setq currobj (ssadd (entlast) currobj))
(setq coords (list 
(list 3840.5625 256.1291) 
(list 3914.585 256.7791) 
(list 3914.585 256.9561) 
(list 3840.5625 256.2061)))
(apply 'command (append '("pline") coords '("c")))
(setq currobj (ssadd (entlast) currobj))
(setq coords (list 
(list 3839.4375 256.2061) 
(list 3765.415 256.9561) 
(list 3765.415 256.7791) 
(list 3839.4375 256.1291)))
(apply 'command (append '("pline") coords '("c")))
(setq currobj (ssadd (entlast) currobj))
(setq coords (list 
(list 3839.4375 255.9861) 
(list 3765.415 256.6361) 
(list 3765.415 256.4591) 
(list 3839.4375 255.9091)))
(apply 'command (append '("pline") coords '("c")))
(setq currobj (ssadd (entlast) currobj))
(setq coords (list 
(list 3839.4375 255.7661) 
(list 3765.415 256.3161) 
(list 3765.415 256.1391) 
(list 3839.4375 255.6891)))
(apply 'command (append '("pline") coords '("c")))
(setq currobj (ssadd (entlast) currobj))
(setq coords (list 
(list 3839.4375 255.5461) 
(list 3765.415 255.9961) 
(list 3765.415 255.8191) 
(list 3839.4375 255.4691)))
(apply 'command (append '("pline") coords '("c")))
(setq currobj (ssadd (entlast) currobj))
(setq coords (list 
(list 3839.4375 255.3261) 
(list 3765.415 255.6761) 
(list 3765.415 255.4991) 
(list 3839.4375 255.2491)))
(apply 'command (append '("pline") coords '("c")))
(setq currobj (ssadd (entlast) currobj))
(setq coords (list 
(list 3839.4375 255.1061) 
(list 3765.415 255.3561) 
(list 3765.415 255.1791) 
(list 3839.4375 255.0291)))
(apply 'command (append '("pline") coords '("c")))
(setq currobj (ssadd (entlast) currobj))
(setq coords (list 
(list 3839.4375 254.8861) 
(list 3765.415 255.0361) 
(list 3765.415 254.8591) 
(list 3839.4375 254.8091)))
(apply 'command (append '("pline") coords '("c")))
(setq currobj (ssadd (entlast) currobj))
(setq coords (list 
(list 3839.4375 254.6661) 
(list 3765.415 254.7161) 
(list 3765.415 254.5391) 
(list 3839.4375 254.5891)))
(apply 'command (append '("pline") coords '("c")))
(setq currobj (ssadd (entlast) currobj))
(setq coords (list 
(list 3839.4375 254.4461) 
(list 3765.415 254.3961) 
(list 3765.415 254.2191) 
(list 3839.4375 254.3691)))
(apply 'command (append '("pline") coords '("c")))
(setq currobj (ssadd (entlast) currobj))
(setq coords (list 
(list 3839.4375 254.2261) 
(list 3765.415 254.0761) 
(list 3765.415 253.8991) 
(list 3839.4375 254.1491)))
(apply 'command (append '("pline") coords '("c")))
(setq currobj (ssadd (entlast) currobj))
(setq coords (list 
(list 3839.4375 254.0061) 
(list 3765.415 253.7561) 
(list 3765.415 253.5791) 
(list 3839.4375 253.9291)))
(apply 'command (append '("pline") coords '("c")))
(setq currobj (ssadd (entlast) currobj))
(setq coords (list 
(list 3839.4375 253.7861) 
(list 3765.415 253.4361) 
(list 3765.415 253.2591) 
(list 3839.4375 253.7091)))
(apply 'command (append '("pline") coords '("c")))
(setq currobj (ssadd (entlast) currobj))
(setq coords (list 
(list 3839.4375 253.5661) 
(list 3765.415 253.1161) 
(list 3765.415 252.9391) 
(list 3839.4375 253.4891)))
(apply 'command (append '("pline") coords '("c")))
(setq currobj (ssadd (entlast) currobj))
(setq coords (list 
(list 3839.4375 253.3461) 
(list 3765.415 252.7961) 
(list 3765.415 252.6191) 
(list 3839.4375 253.2691)))
(apply 'command (append '("pline") coords '("c")))
(setq currobj (ssadd (entlast) currobj))
(setq coords (list 
(list 3839.4375 253.1261) 
(list 3765.415 252.4761) 
(list 3765.415 252.2991) 
(list 3839.4375 253.0491)))
(apply 'command (append '("pline") coords '("c")))
(setq currobj (ssadd (entlast) currobj))
(command "_layer" "set" "nitride" "")
(command "_layer" "set" "text" "")
(command "_circle" "3839.0625,241.9061" "0.075")
(command "_circle" "3839.0625,242.2061" "0.075")
(command "_circle" "3839.0625,242.5061" "0.075")
(command "_circle" "3839.0625,242.8061" "0.075")
(command "_circle" "3839.0625,243.1061" "0.075")
(command "_circle" "3838.7625,241.9061" "0.075")
(command "_circle" "3838.7625,242.2061" "0.075")
(command "_circle" "3838.7625,242.5061" "0.075")
(command "_circle" "3838.7625,242.8061" "0.075")
(command "_circle" "3838.7625,243.1061" "0.075")
(command "_circle" "3838.4625,241.9061" "0.075")
(command "_circle" "3838.4625,242.2061" "0.075")
(command "_circle" "3838.4625,242.5061" "0.075")
(command "_circle" "3838.4625,242.8061" "0.075")
(command "_circle" "3838.4625,243.1061" "0.075")
(command "_circle" "3838.1625,241.9061" "0.075")
(command "_circle" "3838.1625,242.2061" "0.075")
(command "_circle" "3838.1625,242.5061" "0.075")
(command "_circle" "3838.1625,242.8061" "0.075")
(command "_circle" "3838.1625,243.1061" "0.075")
(command "_circle" "3837.8625,241.9061" "0.075")
(command "_circle" "3837.8625,242.2061" "0.075")
(command "_circle" "3837.8625,242.5061" "0.075")
(command "_circle" "3837.8625,242.8061" "0.075")
(command "_circle" "3837.8625,243.1061" "0.075")
(command "_layer" "set" "nitride" "")
(setq coords (list 
(list 3840.2625 267.3491) 
(list 3840.2625 382.9939) 
(list 3839.7375 382.9939) 
(list 3839.7375 267.3491)))
(apply 'command (append '("pline") coords '("c")))
(setq currobj (ssadd (entlast) currobj))
(command "_layer" "set" "prebias" "")
(command "_rectangle" "3839.7375,267.3491" "3840.2625,382.9939")
(setq currobj (ssadd (entlast) currobj))
(command "_layer" "set" "nitride" "")
(setq coords (list 
(list 3840.2625 382.9939) 
(list 3840.5625 392.9939) 
(list 3840.5625 392.9939) 
(list 3840.5625 393.9939) 
(list 3914.585 393.2439) 
(list 3914.585 398.1869) 
(list 3840.5625 397.4369) 
(list 3840.5625 398.4369) 
(list 3840.5625 398.4369) 
(list 3840.2625 408.4369) 
(list 3839.7375 408.4369) 
(list 3839.4375 398.4369) 
(list 3839.4375 398.4369) 
(list 3839.4375 397.4369) 
(list 3765.415 398.1869) 
(list 3765.415 393.2439) 
(list 3839.4375 393.9939) 
(list 3839.4375 392.9939) 
(list 3839.4375 392.9939) 
(list 3839.7375 382.9939)))
(apply 'command (append '("pline") coords '("c")))
(setq currobj (ssadd (entlast) currobj))
(command "_layer" "set" "prebias" "")
(setq coords (list 
(list 3839.4375 382.9939) 
(list 3839.4375 393.9939) 
(list 3765.415 393.2439) 
(list 3765.415 398.1869) 
(list 3839.4375 397.4369) 
(list 3839.4375 408.4369) 
(list 3840.5625 408.4369) 
(list 3840.5625 397.4369) 
(list 3914.585 398.1869) 
(list 3914.585 393.2439) 
(list 3840.5625 393.9939) 
(list 3840.5625 382.9939)))
(apply 'command (append '("pline") coords '("c")))
(setq currobj (ssadd (entlast) currobj))
(command "_layer" "set" "nitride" "")
(command "_layer" "set" "fda1" "")
(setq coords (list 
(list 3840.5625 394.1369) 
(list 3914.585 393.3869) 
(list 3914.585 393.5639) 
(list 3840.5625 394.2139)))
(apply 'command (append '("pline") coords '("c")))
(setq currobj (ssadd (entlast) currobj))
(setq coords (list 
(list 3840.5625 394.3569) 
(list 3914.585 393.7069) 
(list 3914.585 393.8839) 
(list 3840.5625 394.4339)))
(apply 'command (append '("pline") coords '("c")))
(setq currobj (ssadd (entlast) currobj))
(setq coords (list 
(list 3840.5625 394.5769) 
(list 3914.585 394.0269) 
(list 3914.585 394.2039) 
(list 3840.5625 394.6539)))
(apply 'command (append '("pline") coords '("c")))
(setq currobj (ssadd (entlast) currobj))
(setq coords (list 
(list 3840.5625 394.7969) 
(list 3914.585 394.3469) 
(list 3914.585 394.5239) 
(list 3840.5625 394.8739)))
(apply 'command (append '("pline") coords '("c")))
(setq currobj (ssadd (entlast) currobj))
(setq coords (list 
(list 3840.5625 395.0169) 
(list 3914.585 394.6669) 
(list 3914.585 394.8439) 
(list 3840.5625 395.0939)))
(apply 'command (append '("pline") coords '("c")))
(setq currobj (ssadd (entlast) currobj))
(setq coords (list 
(list 3840.5625 395.2369) 
(list 3914.585 394.9869) 
(list 3914.585 395.1639) 
(list 3840.5625 395.3139)))
(apply 'command (append '("pline") coords '("c")))
(setq currobj (ssadd (entlast) currobj))
(setq coords (list 
(list 3840.5625 395.4569) 
(list 3914.585 395.3069) 
(list 3914.585 395.4839) 
(list 3840.5625 395.5339)))
(apply 'command (append '("pline") coords '("c")))
(setq currobj (ssadd (entlast) currobj))
(setq coords (list 
(list 3840.5625 395.6769) 
(list 3914.585 395.6269) 
(list 3914.585 395.8039) 
(list 3840.5625 395.7539)))
(apply 'command (append '("pline") coords '("c")))
(setq currobj (ssadd (entlast) currobj))
(setq coords (list 
(list 3840.5625 395.8969) 
(list 3914.585 395.9469) 
(list 3914.585 396.1239) 
(list 3840.5625 395.9739)))
(apply 'command (append '("pline") coords '("c")))
(setq currobj (ssadd (entlast) currobj))
(setq coords (list 
(list 3840.5625 396.1169) 
(list 3914.585 396.2669) 
(list 3914.585 396.4439) 
(list 3840.5625 396.1939)))
(apply 'command (append '("pline") coords '("c")))
(setq currobj (ssadd (entlast) currobj))
(setq coords (list 
(list 3840.5625 396.3369) 
(list 3914.585 396.5869) 
(list 3914.585 396.7639) 
(list 3840.5625 396.4139)))
(apply 'command (append '("pline") coords '("c")))
(setq currobj (ssadd (entlast) currobj))
(setq coords (list 
(list 3840.5625 396.5569) 
(list 3914.585 396.9069) 
(list 3914.585 397.0839) 
(list 3840.5625 396.6339)))
(apply 'command (append '("pline") coords '("c")))
(setq currobj (ssadd (entlast) currobj))
(setq coords (list 
(list 3840.5625 396.7769) 
(list 3914.585 397.2269) 
(list 3914.585 397.4039) 
(list 3840.5625 396.8539)))
(apply 'command (append '("pline") coords '("c")))
(setq currobj (ssadd (entlast) currobj))
(setq coords (list 
(list 3840.5625 396.9969) 
(list 3914.585 397.5469) 
(list 3914.585 397.7239) 
(list 3840.5625 397.0739)))
(apply 'command (append '("pline") coords '("c")))
(setq currobj (ssadd (entlast) currobj))
(setq coords (list 
(list 3840.5625 397.2169) 
(list 3914.585 397.8669) 
(list 3914.585 398.0439) 
(list 3840.5625 397.2939)))
(apply 'command (append '("pline") coords '("c")))
(setq currobj (ssadd (entlast) currobj))
(setq coords (list 
(list 3839.4375 397.2939) 
(list 3765.415 398.0439) 
(list 3765.415 397.8669) 
(list 3839.4375 397.2169)))
(apply 'command (append '("pline") coords '("c")))
(setq currobj (ssadd (entlast) currobj))
(setq coords (list 
(list 3839.4375 397.0739) 
(list 3765.415 397.7239) 
(list 3765.415 397.5469) 
(list 3839.4375 396.9969)))
(apply 'command (append '("pline") coords '("c")))
(setq currobj (ssadd (entlast) currobj))
(setq coords (list 
(list 3839.4375 396.8539) 
(list 3765.415 397.4039) 
(list 3765.415 397.2269) 
(list 3839.4375 396.7769)))
(apply 'command (append '("pline") coords '("c")))
(setq currobj (ssadd (entlast) currobj))
(setq coords (list 
(list 3839.4375 396.6339) 
(list 3765.415 397.0839) 
(list 3765.415 396.9069) 
(list 3839.4375 396.5569)))
(apply 'command (append '("pline") coords '("c")))
(setq currobj (ssadd (entlast) currobj))
(setq coords (list 
(list 3839.4375 396.4139) 
(list 3765.415 396.7639) 
(list 3765.415 396.5869) 
(list 3839.4375 396.3369)))
(apply 'command (append '("pline") coords '("c")))
(setq currobj (ssadd (entlast) currobj))
(setq coords (list 
(list 3839.4375 396.1939) 
(list 3765.415 396.4439) 
(list 3765.415 396.2669) 
(list 3839.4375 396.1169)))
(apply 'command (append '("pline") coords '("c")))
(setq currobj (ssadd (entlast) currobj))
(setq coords (list 
(list 3839.4375 395.9739) 
(list 3765.415 396.1239) 
(list 3765.415 395.9469) 
(list 3839.4375 395.8969)))
(apply 'command (append '("pline") coords '("c")))
(setq currobj (ssadd (entlast) currobj))
(setq coords (list 
(list 3839.4375 395.7539) 
(list 3765.415 395.8039) 
(list 3765.415 395.6269) 
(list 3839.4375 395.6769)))
(apply 'command (append '("pline") coords '("c")))
(setq currobj (ssadd (entlast) currobj))
(setq coords (list 
(list 3839.4375 395.5339) 
(list 3765.415 395.4839) 
(list 3765.415 395.3069) 
(list 3839.4375 395.4569)))
(apply 'command (append '("pline") coords '("c")))
(setq currobj (ssadd (entlast) currobj))
(setq coords (list 
(list 3839.4375 395.3139) 
(list 3765.415 395.1639) 
(list 3765.415 394.9869) 
(list 3839.4375 395.2369)))
(apply 'command (append '("pline") coords '("c")))
(setq currobj (ssadd (entlast) currobj))
(setq coords (list 
(list 3839.4375 395.0939) 
(list 3765.415 394.8439) 
(list 3765.415 394.6669) 
(list 3839.4375 395.0169)))
(apply 'command (append '("pline") coords '("c")))
(setq currobj (ssadd (entlast) currobj))
(setq coords (list 
(list 3839.4375 394.8739) 
(list 3765.415 394.5239) 
(list 3765.415 394.3469) 
(list 3839.4375 394.7969)))
(apply 'command (append '("pline") coords '("c")))
(setq currobj (ssadd (entlast) currobj))
(setq coords (list 
(list 3839.4375 394.6539) 
(list 3765.415 394.2039) 
(list 3765.415 394.0269) 
(list 3839.4375 394.5769)))
(apply 'command (append '("pline") coords '("c")))
(setq currobj (ssadd (entlast) currobj))
(setq coords (list 
(list 3839.4375 394.4339) 
(list 3765.415 393.8839) 
(list 3765.415 393.7069) 
(list 3839.4375 394.3569)))
(apply 'command (append '("pline") coords '("c")))
(setq currobj (ssadd (entlast) currobj))
(setq coords (list 
(list 3839.4375 394.2139) 
(list 3765.415 393.5639) 
(list 3765.415 393.3869) 
(list 3839.4375 394.1369)))
(apply 'command (append '("pline") coords '("c")))
(setq currobj (ssadd (entlast) currobj))
(command "_layer" "set" "nitride" "")
(command "_layer" "set" "text" "")
(command "_circle" "3839.0625,382.9939" "0.075")
(command "_circle" "3839.0625,383.2939" "0.075")
(command "_circle" "3839.0625,383.5939" "0.075")
(command "_circle" "3839.0625,383.8939" "0.075")
(command "_circle" "3839.0625,384.1939" "0.075")
(command "_circle" "3838.7625,382.9939" "0.075")
(command "_circle" "3838.7625,383.2939" "0.075")
(command "_circle" "3838.7625,383.5939" "0.075")
(command "_circle" "3838.7625,383.8939" "0.075")
(command "_circle" "3838.7625,384.1939" "0.075")
(command "_circle" "3838.4625,382.9939" "0.075")
(command "_circle" "3838.4625,383.2939" "0.075")
(command "_circle" "3838.4625,383.5939" "0.075")
(command "_circle" "3838.4625,383.8939" "0.075")
(command "_circle" "3838.4625,384.1939" "0.075")
(command "_circle" "3838.1625,382.9939" "0.075")
(command "_circle" "3838.1625,383.2939" "0.075")
(command "_circle" "3838.1625,383.5939" "0.075")
(command "_circle" "3838.1625,383.8939" "0.075")
(command "_circle" "3838.1625,384.1939" "0.075")
(command "_circle" "3837.8625,382.9939" "0.075")
(command "_circle" "3837.8625,383.2939" "0.075")
(command "_circle" "3837.8625,383.5939" "0.075")
(command "_circle" "3837.8625,383.8939" "0.075")
(command "_circle" "3837.8625,384.1939" "0.075")
(command "_layer" "set" "nitride" "")
(setq coords (list 
(list 3840.2625 408.4369) 
(list 3840.2625 524.0816) 
(list 3839.7375 524.0816) 
(list 3839.7375 408.4369)))
(apply 'command (append '("pline") coords '("c")))
(setq currobj (ssadd (entlast) currobj))
(command "_layer" "set" "prebias" "")
(command "_rectangle" "3839.7375,408.4369" "3840.2625,524.0816")
(setq currobj (ssadd (entlast) currobj))
(command "_layer" "set" "nitride" "")
(setq coords (list 
(list 3840.2625 524.0816) 
(list 3840.5625 534.0816) 
(list 3840.5625 534.0816) 
(list 3840.5625 535.0816) 
(list 3914.585 534.3316) 
(list 3914.585 539.2746) 
(list 3840.5625 538.5246) 
(list 3840.5625 539.5246) 
(list 3840.5625 539.5246) 
(list 3840.2625 549.5246) 
(list 3839.7375 549.5246) 
(list 3839.4375 539.5246) 
(list 3839.4375 539.5246) 
(list 3839.4375 538.5246) 
(list 3765.415 539.2746) 
(list 3765.415 534.3316) 
(list 3839.4375 535.0816) 
(list 3839.4375 534.0816) 
(list 3839.4375 534.0816) 
(list 3839.7375 524.0816)))
(apply 'command (append '("pline") coords '("c")))
(setq currobj (ssadd (entlast) currobj))
(command "_layer" "set" "prebias" "")
(setq coords (list 
(list 3839.4375 524.0816) 
(list 3839.4375 535.0816) 
(list 3765.415 534.3316) 
(list 3765.415 539.2746) 
(list 3839.4375 538.5246) 
(list 3839.4375 549.5246) 
(list 3840.5625 549.5246) 
(list 3840.5625 538.5246) 
(list 3914.585 539.2746) 
(list 3914.585 534.3316) 
(list 3840.5625 535.0816) 
(list 3840.5625 524.0816)))
(apply 'command (append '("pline") coords '("c")))
(setq currobj (ssadd (entlast) currobj))
(command "_layer" "set" "nitride" "")
(command "_layer" "set" "fda1" "")
(setq coords (list 
(list 3840.5625 535.2246) 
(list 3914.585 534.4746) 
(list 3914.585 534.6516) 
(list 3840.5625 535.3016)))
(apply 'command (append '("pline") coords '("c")))
(setq currobj (ssadd (entlast) currobj))
(setq coords (list 
(list 3840.5625 535.4446) 
(list 3914.585 534.7946) 
(list 3914.585 534.9716) 
(list 3840.5625 535.5216)))
(apply 'command (append '("pline") coords '("c")))
(setq currobj (ssadd (entlast) currobj))
(setq coords (list 
(list 3840.5625 535.6646) 
(list 3914.585 535.1146) 
(list 3914.585 535.2916) 
(list 3840.5625 535.7416)))
(apply 'command (append '("pline") coords '("c")))
(setq currobj (ssadd (entlast) currobj))
(setq coords (list 
(list 3840.5625 535.8846) 
(list 3914.585 535.4346) 
(list 3914.585 535.6116) 
(list 3840.5625 535.9616)))
(apply 'command (append '("pline") coords '("c")))
(setq currobj (ssadd (entlast) currobj))
(setq coords (list 
(list 3840.5625 536.1046) 
(list 3914.585 535.7546) 
(list 3914.585 535.9316) 
(list 3840.5625 536.1816)))
(apply 'command (append '("pline") coords '("c")))
(setq currobj (ssadd (entlast) currobj))
(setq coords (list 
(list 3840.5625 536.3246) 
(list 3914.585 536.0746) 
(list 3914.585 536.2516) 
(list 3840.5625 536.4016)))
(apply 'command (append '("pline") coords '("c")))
(setq currobj (ssadd (entlast) currobj))
(setq coords (list 
(list 3840.5625 536.5446) 
(list 3914.585 536.3946) 
(list 3914.585 536.5716) 
(list 3840.5625 536.6216)))
(apply 'command (append '("pline") coords '("c")))
(setq currobj (ssadd (entlast) currobj))
(setq coords (list 
(list 3840.5625 536.7646) 
(list 3914.585 536.7146) 
(list 3914.585 536.8916) 
(list 3840.5625 536.8416)))
(apply 'command (append '("pline") coords '("c")))
(setq currobj (ssadd (entlast) currobj))
(setq coords (list 
(list 3840.5625 536.9846) 
(list 3914.585 537.0346) 
(list 3914.585 537.2116) 
(list 3840.5625 537.0616)))
(apply 'command (append '("pline") coords '("c")))
(setq currobj (ssadd (entlast) currobj))
(setq coords (list 
(list 3840.5625 537.2046) 
(list 3914.585 537.3546) 
(list 3914.585 537.5316) 
(list 3840.5625 537.2816)))
(apply 'command (append '("pline") coords '("c")))
(setq currobj (ssadd (entlast) currobj))
(setq coords (list 
(list 3840.5625 537.4246) 
(list 3914.585 537.6746) 
(list 3914.585 537.8516) 
(list 3840.5625 537.5016)))
(apply 'command (append '("pline") coords '("c")))
(setq currobj (ssadd (entlast) currobj))
(setq coords (list 
(list 3840.5625 537.6446) 
(list 3914.585 537.9946) 
(list 3914.585 538.1716) 
(list 3840.5625 537.7216)))
(apply 'command (append '("pline") coords '("c")))
(setq currobj (ssadd (entlast) currobj))
(setq coords (list 
(list 3840.5625 537.8646) 
(list 3914.585 538.3146) 
(list 3914.585 538.4916) 
(list 3840.5625 537.9416)))
(apply 'command (append '("pline") coords '("c")))
(setq currobj (ssadd (entlast) currobj))
(setq coords (list 
(list 3840.5625 538.0846) 
(list 3914.585 538.6346) 
(list 3914.585 538.8116) 
(list 3840.5625 538.1616)))
(apply 'command (append '("pline") coords '("c")))
(setq currobj (ssadd (entlast) currobj))
(setq coords (list 
(list 3840.5625 538.3046) 
(list 3914.585 538.9546) 
(list 3914.585 539.1316) 
(list 3840.5625 538.3816)))
(apply 'command (append '("pline") coords '("c")))
(setq currobj (ssadd (entlast) currobj))
(setq coords (list 
(list 3839.4375 538.3816) 
(list 3765.415 539.1316) 
(list 3765.415 538.9546) 
(list 3839.4375 538.3046)))
(apply 'command (append '("pline") coords '("c")))
(setq currobj (ssadd (entlast) currobj))
(setq coords (list 
(list 3839.4375 538.1616) 
(list 3765.415 538.8116) 
(list 3765.415 538.6346) 
(list 3839.4375 538.0846)))
(apply 'command (append '("pline") coords '("c")))
(setq currobj (ssadd (entlast) currobj))
(setq coords (list 
(list 3839.4375 537.9416) 
(list 3765.415 538.4916) 
(list 3765.415 538.3146) 
(list 3839.4375 537.8646)))
(apply 'command (append '("pline") coords '("c")))
(setq currobj (ssadd (entlast) currobj))
(setq coords (list 
(list 3839.4375 537.7216) 
(list 3765.415 538.1716) 
(list 3765.415 537.9946) 
(list 3839.4375 537.6446)))
(apply 'command (append '("pline") coords '("c")))
(setq currobj (ssadd (entlast) currobj))
(setq coords (list 
(list 3839.4375 537.5016) 
(list 3765.415 537.8516) 
(list 3765.415 537.6746) 
(list 3839.4375 537.4246)))
(apply 'command (append '("pline") coords '("c")))
(setq currobj (ssadd (entlast) currobj))
(setq coords (list 
(list 3839.4375 537.2816) 
(list 3765.415 537.5316) 
(list 3765.415 537.3546) 
(list 3839.4375 537.2046)))
(apply 'command (append '("pline") coords '("c")))
(setq currobj (ssadd (entlast) currobj))
(setq coords (list 
(list 3839.4375 537.0616) 
(list 3765.415 537.2116) 
(list 3765.415 537.0346) 
(list 3839.4375 536.9846)))
(apply 'command (append '("pline") coords '("c")))
(setq currobj (ssadd (entlast) currobj))
(setq coords (list 
(list 3839.4375 536.8416) 
(list 3765.415 536.8916) 
(list 3765.415 536.7146) 
(list 3839.4375 536.7646)))
(apply 'command (append '("pline") coords '("c")))
(setq currobj (ssadd (entlast) currobj))
(setq coords (list 
(list 3839.4375 536.6216) 
(list 3765.415 536.5716) 
(list 3765.415 536.3946) 
(list 3839.4375 536.5446)))
(apply 'command (append '("pline") coords '("c")))
(setq currobj (ssadd (entlast) currobj))
(setq coords (list 
(list 3839.4375 536.4016) 
(list 3765.415 536.2516) 
(list 3765.415 536.0746) 
(list 3839.4375 536.3246)))
(apply 'command (append '("pline") coords '("c")))
(setq currobj (ssadd (entlast) currobj))
(setq coords (list 
(list 3839.4375 536.1816) 
(list 3765.415 535.9316) 
(list 3765.415 535.7546) 
(list 3839.4375 536.1046)))
(apply 'command (append '("pline") coords '("c")))
(setq currobj (ssadd (entlast) currobj))
(setq coords (list 
(list 3839.4375 535.9616) 
(list 3765.415 535.6116) 
(list 3765.415 535.4346) 
(list 3839.4375 535.8846)))
(apply 'command (append '("pline") coords '("c")))
(setq currobj (ssadd (entlast) currobj))
(setq coords (list 
(list 3839.4375 535.7416) 
(list 3765.415 535.2916) 
(list 3765.415 535.1146) 
(list 3839.4375 535.6646)))
(apply 'command (append '("pline") coords '("c")))
(setq currobj (ssadd (entlast) currobj))
(setq coords (list 
(list 3839.4375 535.5216) 
(list 3765.415 534.9716) 
(list 3765.415 534.7946) 
(list 3839.4375 535.4446)))
(apply 'command (append '("pline") coords '("c")))
(setq currobj (ssadd (entlast) currobj))
(setq coords (list 
(list 3839.4375 535.3016) 
(list 3765.415 534.6516) 
(list 3765.415 534.4746) 
(list 3839.4375 535.2246)))
(apply 'command (append '("pline") coords '("c")))
(setq currobj (ssadd (entlast) currobj))
(command "_layer" "set" "nitride" "")
(command "_layer" "set" "text" "")
(command "_circle" "3839.0625,524.0816" "0.075")
(command "_circle" "3839.0625,524.3816" "0.075")
(command "_circle" "3839.0625,524.6816" "0.075")
(command "_circle" "3839.0625,524.9816" "0.075")
(command "_circle" "3839.0625,525.2816" "0.075")
(command "_circle" "3838.7625,524.0816" "0.075")
(command "_circle" "3838.7625,524.3816" "0.075")
(command "_circle" "3838.7625,524.6816" "0.075")
(command "_circle" "3838.7625,524.9816" "0.075")
(command "_circle" "3838.7625,525.2816" "0.075")
(command "_circle" "3838.4625,524.0816" "0.075")
(command "_circle" "3838.4625,524.3816" "0.075")
(command "_circle" "3838.4625,524.6816" "0.075")
(command "_circle" "3838.4625,524.9816" "0.075")
(command "_circle" "3838.4625,525.2816" "0.075")
(command "_circle" "3838.1625,524.0816" "0.075")
(command "_circle" "3838.1625,524.3816" "0.075")
(command "_circle" "3838.1625,524.6816" "0.075")
(command "_circle" "3838.1625,524.9816" "0.075")
(command "_circle" "3838.1625,525.2816" "0.075")
(command "_circle" "3837.8625,524.0816" "0.075")
(command "_circle" "3837.8625,524.3816" "0.075")
(command "_circle" "3837.8625,524.6816" "0.075")
(command "_circle" "3837.8625,524.9816" "0.075")
(command "_circle" "3837.8625,525.2816" "0.075")
(command "_layer" "set" "nitride" "")
(setq coords (list 
(list 3840.2625 549.5246) 
(list 3840.2625 665.1693) 
(list 3839.7375 665.1693) 
(list 3839.7375 549.5246)))
(apply 'command (append '("pline") coords '("c")))
(setq currobj (ssadd (entlast) currobj))
(command "_layer" "set" "prebias" "")
(command "_rectangle" "3839.7375,549.5246" "3840.2625,665.1693")
(setq currobj (ssadd (entlast) currobj))
(command "_layer" "set" "nitride" "")
(setq coords (list 
(list 3840.2625 665.1693) 
(list 3840.5625 675.1693) 
(list 3840.5625 675.1693) 
(list 3840.5625 676.1693) 
(list 3914.585 675.4193) 
(list 3914.585 680.3623) 
(list 3840.5625 679.6123) 
(list 3840.5625 680.6123) 
(list 3840.5625 680.6123) 
(list 3840.2625 690.6123) 
(list 3839.7375 690.6123) 
(list 3839.4375 680.6123) 
(list 3839.4375 680.6123) 
(list 3839.4375 679.6123) 
(list 3765.415 680.3623) 
(list 3765.415 675.4193) 
(list 3839.4375 676.1693) 
(list 3839.4375 675.1693) 
(list 3839.4375 675.1693) 
(list 3839.7375 665.1693)))
(apply 'command (append '("pline") coords '("c")))
(setq currobj (ssadd (entlast) currobj))
(command "_layer" "set" "prebias" "")
(setq coords (list 
(list 3839.4375 665.1693) 
(list 3839.4375 676.1693) 
(list 3765.415 675.4193) 
(list 3765.415 680.3623) 
(list 3839.4375 679.6123) 
(list 3839.4375 690.6123) 
(list 3840.5625 690.6123) 
(list 3840.5625 679.6123) 
(list 3914.585 680.3623) 
(list 3914.585 675.4193) 
(list 3840.5625 676.1693) 
(list 3840.5625 665.1693)))
(apply 'command (append '("pline") coords '("c")))
(setq currobj (ssadd (entlast) currobj))
(command "_layer" "set" "nitride" "")
(command "_layer" "set" "fda1" "")
(setq coords (list 
(list 3840.5625 676.3123) 
(list 3914.585 675.5623) 
(list 3914.585 675.7393) 
(list 3840.5625 676.3893)))
(apply 'command (append '("pline") coords '("c")))
(setq currobj (ssadd (entlast) currobj))
(setq coords (list 
(list 3840.5625 676.5323) 
(list 3914.585 675.8823) 
(list 3914.585 676.0593) 
(list 3840.5625 676.6093)))
(apply 'command (append '("pline") coords '("c")))
(setq currobj (ssadd (entlast) currobj))
(setq coords (list 
(list 3840.5625 676.7523) 
(list 3914.585 676.2023) 
(list 3914.585 676.3793) 
(list 3840.5625 676.8293)))
(apply 'command (append '("pline") coords '("c")))
(setq currobj (ssadd (entlast) currobj))
(setq coords (list 
(list 3840.5625 676.9723) 
(list 3914.585 676.5223) 
(list 3914.585 676.6993) 
(list 3840.5625 677.0493)))
(apply 'command (append '("pline") coords '("c")))
(setq currobj (ssadd (entlast) currobj))
(setq coords (list 
(list 3840.5625 677.1923) 
(list 3914.585 676.8423) 
(list 3914.585 677.0193) 
(list 3840.5625 677.2693)))
(apply 'command (append '("pline") coords '("c")))
(setq currobj (ssadd (entlast) currobj))
(setq coords (list 
(list 3840.5625 677.4123) 
(list 3914.585 677.1623) 
(list 3914.585 677.3393) 
(list 3840.5625 677.4893)))
(apply 'command (append '("pline") coords '("c")))
(setq currobj (ssadd (entlast) currobj))
(setq coords (list 
(list 3840.5625 677.6323) 
(list 3914.585 677.4823) 
(list 3914.585 677.6593) 
(list 3840.5625 677.7093)))
(apply 'command (append '("pline") coords '("c")))
(setq currobj (ssadd (entlast) currobj))
(setq coords (list 
(list 3840.5625 677.8523) 
(list 3914.585 677.8023) 
(list 3914.585 677.9793) 
(list 3840.5625 677.9293)))
(apply 'command (append '("pline") coords '("c")))
(setq currobj (ssadd (entlast) currobj))
(setq coords (list 
(list 3840.5625 678.0723) 
(list 3914.585 678.1223) 
(list 3914.585 678.2993) 
(list 3840.5625 678.1493)))
(apply 'command (append '("pline") coords '("c")))
(setq currobj (ssadd (entlast) currobj))
(setq coords (list 
(list 3840.5625 678.2923) 
(list 3914.585 678.4423) 
(list 3914.585 678.6193) 
(list 3840.5625 678.3693)))
(apply 'command (append '("pline") coords '("c")))
(setq currobj (ssadd (entlast) currobj))
(setq coords (list 
(list 3840.5625 678.5123) 
(list 3914.585 678.7623) 
(list 3914.585 678.9393) 
(list 3840.5625 678.5893)))
(apply 'command (append '("pline") coords '("c")))
(setq currobj (ssadd (entlast) currobj))
(setq coords (list 
(list 3840.5625 678.7323) 
(list 3914.585 679.0823) 
(list 3914.585 679.2593) 
(list 3840.5625 678.8093)))
(apply 'command (append '("pline") coords '("c")))
(setq currobj (ssadd (entlast) currobj))
(setq coords (list 
(list 3840.5625 678.9523) 
(list 3914.585 679.4023) 
(list 3914.585 679.5793) 
(list 3840.5625 679.0293)))
(apply 'command (append '("pline") coords '("c")))
(setq currobj (ssadd (entlast) currobj))
(setq coords (list 
(list 3840.5625 679.1723) 
(list 3914.585 679.7223) 
(list 3914.585 679.8993) 
(list 3840.5625 679.2493)))
(apply 'command (append '("pline") coords '("c")))
(setq currobj (ssadd (entlast) currobj))
(setq coords (list 
(list 3840.5625 679.3923) 
(list 3914.585 680.0423) 
(list 3914.585 680.2193) 
(list 3840.5625 679.4693)))
(apply 'command (append '("pline") coords '("c")))
(setq currobj (ssadd (entlast) currobj))
(setq coords (list 
(list 3839.4375 679.4693) 
(list 3765.415 680.2193) 
(list 3765.415 680.0423) 
(list 3839.4375 679.3923)))
(apply 'command (append '("pline") coords '("c")))
(setq currobj (ssadd (entlast) currobj))
(setq coords (list 
(list 3839.4375 679.2493) 
(list 3765.415 679.8993) 
(list 3765.415 679.7223) 
(list 3839.4375 679.1723)))
(apply 'command (append '("pline") coords '("c")))
(setq currobj (ssadd (entlast) currobj))
(setq coords (list 
(list 3839.4375 679.0293) 
(list 3765.415 679.5793) 
(list 3765.415 679.4023) 
(list 3839.4375 678.9523)))
(apply 'command (append '("pline") coords '("c")))
(setq currobj (ssadd (entlast) currobj))
(setq coords (list 
(list 3839.4375 678.8093) 
(list 3765.415 679.2593) 
(list 3765.415 679.0823) 
(list 3839.4375 678.7323)))
(apply 'command (append '("pline") coords '("c")))
(setq currobj (ssadd (entlast) currobj))
(setq coords (list 
(list 3839.4375 678.5893) 
(list 3765.415 678.9393) 
(list 3765.415 678.7623) 
(list 3839.4375 678.5123)))
(apply 'command (append '("pline") coords '("c")))
(setq currobj (ssadd (entlast) currobj))
(setq coords (list 
(list 3839.4375 678.3693) 
(list 3765.415 678.6193) 
(list 3765.415 678.4423) 
(list 3839.4375 678.2923)))
(apply 'command (append '("pline") coords '("c")))
(setq currobj (ssadd (entlast) currobj))
(setq coords (list 
(list 3839.4375 678.1493) 
(list 3765.415 678.2993) 
(list 3765.415 678.1223) 
(list 3839.4375 678.0723)))
(apply 'command (append '("pline") coords '("c")))
(setq currobj (ssadd (entlast) currobj))
(setq coords (list 
(list 3839.4375 677.9293) 
(list 3765.415 677.9793) 
(list 3765.415 677.8023) 
(list 3839.4375 677.8523)))
(apply 'command (append '("pline") coords '("c")))
(setq currobj (ssadd (entlast) currobj))
(setq coords (list 
(list 3839.4375 677.7093) 
(list 3765.415 677.6593) 
(list 3765.415 677.4823) 
(list 3839.4375 677.6323)))
(apply 'command (append '("pline") coords '("c")))
(setq currobj (ssadd (entlast) currobj))
(setq coords (list 
(list 3839.4375 677.4893) 
(list 3765.415 677.3393) 
(list 3765.415 677.1623) 
(list 3839.4375 677.4123)))
(apply 'command (append '("pline") coords '("c")))
(setq currobj (ssadd (entlast) currobj))
(setq coords (list 
(list 3839.4375 677.2693) 
(list 3765.415 677.0193) 
(list 3765.415 676.8423) 
(list 3839.4375 677.1923)))
(apply 'command (append '("pline") coords '("c")))
(setq currobj (ssadd (entlast) currobj))
(setq coords (list 
(list 3839.4375 677.0493) 
(list 3765.415 676.6993) 
(list 3765.415 676.5223) 
(list 3839.4375 676.9723)))
(apply 'command (append '("pline") coords '("c")))
(setq currobj (ssadd (entlast) currobj))
(setq coords (list 
(list 3839.4375 676.8293) 
(list 3765.415 676.3793) 
(list 3765.415 676.2023) 
(list 3839.4375 676.7523)))
(apply 'command (append '("pline") coords '("c")))
(setq currobj (ssadd (entlast) currobj))
(setq coords (list 
(list 3839.4375 676.6093) 
(list 3765.415 676.0593) 
(list 3765.415 675.8823) 
(list 3839.4375 676.5323)))
(apply 'command (append '("pline") coords '("c")))
(setq currobj (ssadd (entlast) currobj))
(setq coords (list 
(list 3839.4375 676.3893) 
(list 3765.415 675.7393) 
(list 3765.415 675.5623) 
(list 3839.4375 676.3123)))
(apply 'command (append '("pline") coords '("c")))
(setq currobj (ssadd (entlast) currobj))
(command "_layer" "set" "nitride" "")
(command "_layer" "set" "text" "")
(command "_circle" "3839.0625,665.1693" "0.075")
(command "_circle" "3839.0625,665.4693" "0.075")
(command "_circle" "3839.0625,665.7693" "0.075")
(command "_circle" "3839.0625,666.0693" "0.075")
(command "_circle" "3839.0625,666.3693" "0.075")
(command "_circle" "3838.7625,665.1693" "0.075")
(command "_circle" "3838.7625,665.4693" "0.075")
(command "_circle" "3838.7625,665.7693" "0.075")
(command "_circle" "3838.7625,666.0693" "0.075")
(command "_circle" "3838.7625,666.3693" "0.075")
(command "_circle" "3838.4625,665.1693" "0.075")
(command "_circle" "3838.4625,665.4693" "0.075")
(command "_circle" "3838.4625,665.7693" "0.075")
(command "_circle" "3838.4625,666.0693" "0.075")
(command "_circle" "3838.4625,666.3693" "0.075")
(command "_circle" "3838.1625,665.1693" "0.075")
(command "_circle" "3838.1625,665.4693" "0.075")
(command "_circle" "3838.1625,665.7693" "0.075")
(command "_circle" "3838.1625,666.0693" "0.075")
(command "_circle" "3838.1625,666.3693" "0.075")
(command "_circle" "3837.8625,665.1693" "0.075")
(command "_circle" "3837.8625,665.4693" "0.075")
(command "_circle" "3837.8625,665.7693" "0.075")
(command "_circle" "3837.8625,666.0693" "0.075")
(command "_circle" "3837.8625,666.3693" "0.075")
(command "_layer" "set" "nitride" "")
(setq coords (list 
(list 3840.2625 690.6123) 
(list 3840.2625 806.257) 
(list 3839.7375 806.257) 
(list 3839.7375 690.6123)))
(apply 'command (append '("pline") coords '("c")))
(setq currobj (ssadd (entlast) currobj))
(command "_layer" "set" "prebias" "")
(command "_rectangle" "3839.7375,690.6123" "3840.2625,806.257")
(setq currobj (ssadd (entlast) currobj))
(command "_layer" "set" "nitride" "")
(setq coords (list 
(list 3840.2625 806.257) 
(list 3840.5625 816.257) 
(list 3840.5625 816.257) 
(list 3840.5625 817.257) 
(list 3914.585 816.507) 
(list 3914.585 821.45) 
(list 3840.5625 820.7) 
(list 3840.5625 821.7) 
(list 3840.5625 821.7) 
(list 3840.2625 831.7) 
(list 3839.7375 831.7) 
(list 3839.4375 821.7) 
(list 3839.4375 821.7) 
(list 3839.4375 820.7) 
(list 3765.415 821.45) 
(list 3765.415 816.507) 
(list 3839.4375 817.257) 
(list 3839.4375 816.257) 
(list 3839.4375 816.257) 
(list 3839.7375 806.257)))
(apply 'command (append '("pline") coords '("c")))
(setq currobj (ssadd (entlast) currobj))
(command "_layer" "set" "prebias" "")
(setq coords (list 
(list 3839.4375 806.257) 
(list 3839.4375 817.257) 
(list 3765.415 816.507) 
(list 3765.415 821.45) 
(list 3839.4375 820.7) 
(list 3839.4375 831.7) 
(list 3840.5625 831.7) 
(list 3840.5625 820.7) 
(list 3914.585 821.45) 
(list 3914.585 816.507) 
(list 3840.5625 817.257) 
(list 3840.5625 806.257)))
(apply 'command (append '("pline") coords '("c")))
(setq currobj (ssadd (entlast) currobj))
(command "_layer" "set" "nitride" "")
(command "_layer" "set" "fda1" "")
(setq coords (list 
(list 3840.5625 817.4) 
(list 3914.585 816.65) 
(list 3914.585 816.827) 
(list 3840.5625 817.477)))
(apply 'command (append '("pline") coords '("c")))
(setq currobj (ssadd (entlast) currobj))
(setq coords (list 
(list 3840.5625 817.62) 
(list 3914.585 816.97) 
(list 3914.585 817.147) 
(list 3840.5625 817.697)))
(apply 'command (append '("pline") coords '("c")))
(setq currobj (ssadd (entlast) currobj))
(setq coords (list 
(list 3840.5625 817.84) 
(list 3914.585 817.29) 
(list 3914.585 817.467) 
(list 3840.5625 817.917)))
(apply 'command (append '("pline") coords '("c")))
(setq currobj (ssadd (entlast) currobj))
(setq coords (list 
(list 3840.5625 818.06) 
(list 3914.585 817.61) 
(list 3914.585 817.787) 
(list 3840.5625 818.137)))
(apply 'command (append '("pline") coords '("c")))
(setq currobj (ssadd (entlast) currobj))
(setq coords (list 
(list 3840.5625 818.28) 
(list 3914.585 817.93) 
(list 3914.585 818.107) 
(list 3840.5625 818.357)))
(apply 'command (append '("pline") coords '("c")))
(setq currobj (ssadd (entlast) currobj))
(setq coords (list 
(list 3840.5625 818.5) 
(list 3914.585 818.25) 
(list 3914.585 818.427) 
(list 3840.5625 818.577)))
(apply 'command (append '("pline") coords '("c")))
(setq currobj (ssadd (entlast) currobj))
(setq coords (list 
(list 3840.5625 818.72) 
(list 3914.585 818.57) 
(list 3914.585 818.747) 
(list 3840.5625 818.797)))
(apply 'command (append '("pline") coords '("c")))
(setq currobj (ssadd (entlast) currobj))
(setq coords (list 
(list 3840.5625 818.94) 
(list 3914.585 818.89) 
(list 3914.585 819.067) 
(list 3840.5625 819.017)))
(apply 'command (append '("pline") coords '("c")))
(setq currobj (ssadd (entlast) currobj))
(setq coords (list 
(list 3840.5625 819.16) 
(list 3914.585 819.21) 
(list 3914.585 819.387) 
(list 3840.5625 819.237)))
(apply 'command (append '("pline") coords '("c")))
(setq currobj (ssadd (entlast) currobj))
(setq coords (list 
(list 3840.5625 819.38) 
(list 3914.585 819.53) 
(list 3914.585 819.707) 
(list 3840.5625 819.457)))
(apply 'command (append '("pline") coords '("c")))
(setq currobj (ssadd (entlast) currobj))
(setq coords (list 
(list 3840.5625 819.6) 
(list 3914.585 819.85) 
(list 3914.585 820.027) 
(list 3840.5625 819.677)))
(apply 'command (append '("pline") coords '("c")))
(setq currobj (ssadd (entlast) currobj))
(setq coords (list 
(list 3840.5625 819.82) 
(list 3914.585 820.17) 
(list 3914.585 820.347) 
(list 3840.5625 819.897)))
(apply 'command (append '("pline") coords '("c")))
(setq currobj (ssadd (entlast) currobj))
(setq coords (list 
(list 3840.5625 820.04) 
(list 3914.585 820.49) 
(list 3914.585 820.667) 
(list 3840.5625 820.117)))
(apply 'command (append '("pline") coords '("c")))
(setq currobj (ssadd (entlast) currobj))
(setq coords (list 
(list 3840.5625 820.26) 
(list 3914.585 820.81) 
(list 3914.585 820.987) 
(list 3840.5625 820.337)))
(apply 'command (append '("pline") coords '("c")))
(setq currobj (ssadd (entlast) currobj))
(setq coords (list 
(list 3840.5625 820.48) 
(list 3914.585 821.13) 
(list 3914.585 821.307) 
(list 3840.5625 820.557)))
(apply 'command (append '("pline") coords '("c")))
(setq currobj (ssadd (entlast) currobj))
(setq coords (list 
(list 3839.4375 820.557) 
(list 3765.415 821.307) 
(list 3765.415 821.13) 
(list 3839.4375 820.48)))
(apply 'command (append '("pline") coords '("c")))
(setq currobj (ssadd (entlast) currobj))
(setq coords (list 
(list 3839.4375 820.337) 
(list 3765.415 820.987) 
(list 3765.415 820.81) 
(list 3839.4375 820.26)))
(apply 'command (append '("pline") coords '("c")))
(setq currobj (ssadd (entlast) currobj))
(setq coords (list 
(list 3839.4375 820.117) 
(list 3765.415 820.667) 
(list 3765.415 820.49) 
(list 3839.4375 820.04)))
(apply 'command (append '("pline") coords '("c")))
(setq currobj (ssadd (entlast) currobj))
(setq coords (list 
(list 3839.4375 819.897) 
(list 3765.415 820.347) 
(list 3765.415 820.17) 
(list 3839.4375 819.82)))
(apply 'command (append '("pline") coords '("c")))
(setq currobj (ssadd (entlast) currobj))
(setq coords (list 
(list 3839.4375 819.677) 
(list 3765.415 820.027) 
(list 3765.415 819.85) 
(list 3839.4375 819.6)))
(apply 'command (append '("pline") coords '("c")))
(setq currobj (ssadd (entlast) currobj))
(setq coords (list 
(list 3839.4375 819.457) 
(list 3765.415 819.707) 
(list 3765.415 819.53) 
(list 3839.4375 819.38)))
(apply 'command (append '("pline") coords '("c")))
(setq currobj (ssadd (entlast) currobj))
(setq coords (list 
(list 3839.4375 819.237) 
(list 3765.415 819.387) 
(list 3765.415 819.21) 
(list 3839.4375 819.16)))
(apply 'command (append '("pline") coords '("c")))
(setq currobj (ssadd (entlast) currobj))
(setq coords (list 
(list 3839.4375 819.017) 
(list 3765.415 819.067) 
(list 3765.415 818.89) 
(list 3839.4375 818.94)))
(apply 'command (append '("pline") coords '("c")))
(setq currobj (ssadd (entlast) currobj))
(setq coords (list 
(list 3839.4375 818.797) 
(list 3765.415 818.747) 
(list 3765.415 818.57) 
(list 3839.4375 818.72)))
(apply 'command (append '("pline") coords '("c")))
(setq currobj (ssadd (entlast) currobj))
(setq coords (list 
(list 3839.4375 818.577) 
(list 3765.415 818.427) 
(list 3765.415 818.25) 
(list 3839.4375 818.5)))
(apply 'command (append '("pline") coords '("c")))
(setq currobj (ssadd (entlast) currobj))
(setq coords (list 
(list 3839.4375 818.357) 
(list 3765.415 818.107) 
(list 3765.415 817.93) 
(list 3839.4375 818.28)))
(apply 'command (append '("pline") coords '("c")))
(setq currobj (ssadd (entlast) currobj))
(setq coords (list 
(list 3839.4375 818.137) 
(list 3765.415 817.787) 
(list 3765.415 817.61) 
(list 3839.4375 818.06)))
(apply 'command (append '("pline") coords '("c")))
(setq currobj (ssadd (entlast) currobj))
(setq coords (list 
(list 3839.4375 817.917) 
(list 3765.415 817.467) 
(list 3765.415 817.29) 
(list 3839.4375 817.84)))
(apply 'command (append '("pline") coords '("c")))
(setq currobj (ssadd (entlast) currobj))
(setq coords (list 
(list 3839.4375 817.697) 
(list 3765.415 817.147) 
(list 3765.415 816.97) 
(list 3839.4375 817.62)))
(apply 'command (append '("pline") coords '("c")))
(setq currobj (ssadd (entlast) currobj))
(setq coords (list 
(list 3839.4375 817.477) 
(list 3765.415 816.827) 
(list 3765.415 816.65) 
(list 3839.4375 817.4)))
(apply 'command (append '("pline") coords '("c")))
(setq currobj (ssadd (entlast) currobj))
(command "_layer" "set" "nitride" "")
(command "_layer" "set" "text" "")
(command "_circle" "3839.0625,806.257" "0.075")
(command "_circle" "3839.0625,806.557" "0.075")
(command "_circle" "3839.0625,806.857" "0.075")
(command "_circle" "3839.0625,807.157" "0.075")
(command "_circle" "3839.0625,807.457" "0.075")
(command "_circle" "3838.7625,806.257" "0.075")
(command "_circle" "3838.7625,806.557" "0.075")
(command "_circle" "3838.7625,806.857" "0.075")
(command "_circle" "3838.7625,807.157" "0.075")
(command "_circle" "3838.7625,807.457" "0.075")
(command "_circle" "3838.4625,806.257" "0.075")
(command "_circle" "3838.4625,806.557" "0.075")
(command "_circle" "3838.4625,806.857" "0.075")
(command "_circle" "3838.4625,807.157" "0.075")
(command "_circle" "3838.4625,807.457" "0.075")
(command "_circle" "3838.1625,806.257" "0.075")
(command "_circle" "3838.1625,806.557" "0.075")
(command "_circle" "3838.1625,806.857" "0.075")
(command "_circle" "3838.1625,807.157" "0.075")
(command "_circle" "3838.1625,807.457" "0.075")
(command "_circle" "3837.8625,806.257" "0.075")
(command "_circle" "3837.8625,806.557" "0.075")
(command "_circle" "3837.8625,806.857" "0.075")
(command "_circle" "3837.8625,807.157" "0.075")
(command "_circle" "3837.8625,807.457" "0.075")
(command "_layer" "set" "nitride" "")
(setq coords (list 
(list 3840.2625 831.7) 
(list 3840.2625 836.7) 
(list 3839.7375 836.7) 
(list 3839.7375 831.7)))
(apply 'command (append '("pline") coords '("c")))
(setq currobj (ssadd (entlast) currobj))
(command "_layer" "set" "prebias" "")
(command "_rectangle" "3839.7375,831.7" "3840.2625,836.7")
(setq currobj (ssadd (entlast) currobj))
(command "_layer" "set" "nitride" "")
(setq cooledsinglenanobeam12 currobj)
(setq currobj nil)
(setq currobj (ssadd))
; DRAWING PHOTONIC CRYSTAL
(command "_layer" "set" "negYjunc" "")
(setq coords (list 
(list 3840.125 866.7) 
(list 3840 851.7) 
(list 3840 866.7)))
(apply 'command (append '("pline") coords '("c")))
(setq currobj (ssadd (entlast) currobj))
(setq coords (list 
(list 3840.2625 836.7) 
(list 3840.405 866.7) 
(list 3841.132 866.7) 
(list 3841.132 836.7)))
(apply 'command (append '("pline") coords '("c")))
(setq currobj (ssadd (entlast) currobj))
(setq coords (list 
(list 3839.875 866.7) 
(list 3840 851.7) 
(list 3840 866.7)))
(apply 'command (append '("pline") coords '("c")))
(setq currobj (ssadd (entlast) currobj))
(setq coords (list 
(list 3839.7375 836.7) 
(list 3839.595 866.7) 
(list 3838.868 866.7) 
(list 3838.868 836.7)))
(apply 'command (append '("pline") coords '("c")))
(setq currobj (ssadd (entlast) currobj))
(command "_layer" "set" "nitride" "")
(setq yjunction12 currobj)
(setq currobj nil)
(setq currobj (ssadd))
(setq tap12 nil)
(setq tap12 (ssadd))
(command "_layer" "set" "phc" "")
(setq coords (list 
(list 3840 866.7) 
(list 3840.125 866.7) 
(list 3840.125 866.7103) 
(list 3840.125 866.7206) 
(list 3840.125 866.7308) 
(list 3840.125 866.7411) 
(list 3840.125 866.7514) 
(list 3840.125 866.7617) 
(list 3840.125 866.7719) 
(list 3840.125 866.7822) 
(list 3840.125 866.7925) 
(list 3840.125 866.8028) 
(list 3840.125 866.8131) 
(list 3840.125 866.8233) 
(list 3840.125 866.8336) 
(list 3840.125 866.8439) 
(list 3840.125 866.8542) 
(list 3840.125 866.8644) 
(list 3840.125 866.8747) 
(list 3840.125 866.885) 
(list 3840.125 866.8953) 
(list 3840.125 866.9056) 
(list 3840.125 866.9158) 
(list 3840.125 866.9261) 
(list 3840.125 866.9364) 
(list 3840.125 866.9467) 
(list 3840.125 866.9569) 
(list 3840.125 866.9672) 
(list 3840.125 866.9775) 
(list 3840.125 866.9878) 
(list 3840.125 866.9981) 
(list 3840.125 867.0083) 
(list 3840.125 867.0186) 
(list 3840.125 867.0289) 
(list 3840.125 867.0392) 
(list 3840.125 867.0494) 
(list 3840.125 867.0597) 
(list 3840.125 867.07) 
(list 3840 867.07)))
(apply 'command (append '("pline") coords '("c")))
(setq tap12 (ssadd (entlast) tap12))
(command "_mirror" (entlast) "" "3840,900" "3840,901" "No")
(setq tap12 (ssadd (entlast) tap12))
(setq coords (list 
(list 3840.4157 866.7) 
(list 3840.405 866.7) 
(list 3840.4053 866.7103) 
(list 3840.4056 866.7206) 
(list 3840.4058 866.7308) 
(list 3840.4059 866.7411) 
(list 3840.406 866.7514) 
(list 3840.406 866.7617) 
(list 3840.4059 866.7719) 
(list 3840.4056 866.7822) 
(list 3840.4053 866.7925) 
(list 3840.4049 866.8028) 
(list 3840.4044 866.8131) 
(list 3840.4038 866.8233) 
(list 3840.4033 866.8336) 
(list 3840.4027 866.8439) 
(list 3840.4021 866.8542) 
(list 3840.4016 866.8644) 
(list 3840.4012 866.8747) 
(list 3840.4009 866.885) 
(list 3840.4007 866.8953) 
(list 3840.4008 866.9056) 
(list 3840.401 866.9158) 
(list 3840.4013 866.9261) 
(list 3840.4019 866.9364) 
(list 3840.4027 866.9467) 
(list 3840.4036 866.9569) 
(list 3840.4047 866.9672) 
(list 3840.4059 866.9775) 
(list 3840.4073 866.9878) 
(list 3840.4086 866.9981) 
(list 3840.41 867.0083) 
(list 3840.4113 867.0186) 
(list 3840.4126 867.0289) 
(list 3840.4137 867.0392) 
(list 3840.4146 867.0494) 
(list 3840.4153 867.0597) 
(list 3840.4157 867.07) 
(list 3840.4157 867.07)))
(apply 'command (append '("pline") coords '("c")))
(setq tap12 (ssadd (entlast) tap12))
(command "_mirror" (entlast) "" "3840,900" "3840,901" "No")
(setq tap12 (ssadd (entlast) tap12))
(setq coords (list 
(list 3841.132 866.7) 
(list 3840.4157 866.7) 
(list 3840.4157 866.7103) 
(list 3840.4157 866.7206) 
(list 3840.4157 866.7308) 
(list 3840.4157 866.7411) 
(list 3840.4157 866.7514) 
(list 3840.4157 866.7617) 
(list 3840.4157 866.7719) 
(list 3840.4157 866.7822) 
(list 3840.4157 866.7925) 
(list 3840.4157 866.8028) 
(list 3840.4157 866.8131) 
(list 3840.4157 866.8233) 
(list 3840.4157 866.8336) 
(list 3840.4157 866.8439) 
(list 3840.4157 866.8542) 
(list 3840.4157 866.8644) 
(list 3840.4157 866.8747) 
(list 3840.4157 866.885) 
(list 3840.4157 866.8953) 
(list 3840.4157 866.9056) 
(list 3840.4157 866.9158) 
(list 3840.4157 866.9261) 
(list 3840.4157 866.9364) 
(list 3840.4157 866.9467) 
(list 3840.4157 866.9569) 
(list 3840.4157 866.9672) 
(list 3840.4157 866.9775) 
(list 3840.4157 866.9878) 
(list 3840.4157 866.9981) 
(list 3840.4157 867.0083) 
(list 3840.4157 867.0186) 
(list 3840.4157 867.0289) 
(list 3840.4157 867.0392) 
(list 3840.4157 867.0494) 
(list 3840.4157 867.0597) 
(list 3840.4157 867.07) 
(list 3841.132 867.07)))
(apply 'command (append '("pline") coords '("c")))
(setq tap12 (ssadd (entlast) tap12))
(command "_mirror" (entlast) "" "3840,900" "3840,901" "No")
(setq tap12 (ssadd (entlast) tap12))
(setq coords (list 
(list 3840 867.07) 
(list 3840.125 867.07) 
(list 3840.125 867.0803) 
(list 3840.125 867.0906) 
(list 3840.125 867.1008) 
(list 3840.125 867.1111) 
(list 3840.125 867.1214) 
(list 3840.125 867.1317) 
(list 3840.125 867.1419) 
(list 3840.125 867.1522) 
(list 3840.125 867.1625) 
(list 3840.125 867.1728) 
(list 3840.125 867.1831) 
(list 3840.125 867.1933) 
(list 3840.125 867.2036) 
(list 3840.125 867.2139) 
(list 3840.125 867.2242) 
(list 3840.125 867.2344) 
(list 3840.125 867.2447) 
(list 3840.125 867.255) 
(list 3840.125 867.2653) 
(list 3840.125 867.2756) 
(list 3840.125 867.2858) 
(list 3840.125 867.2961) 
(list 3840.125 867.3064) 
(list 3840.125 867.3167) 
(list 3840.125 867.3269) 
(list 3840.125 867.3372) 
(list 3840.125 867.3475) 
(list 3840.125 867.3578) 
(list 3840.125 867.3681) 
(list 3840.125 867.3783) 
(list 3840.125 867.3886) 
(list 3840.125 867.3989) 
(list 3840.125 867.4092) 
(list 3840.125 867.4194) 
(list 3840.125 867.4297) 
(list 3840.125 867.44) 
(list 3840 867.44)))
(apply 'command (append '("pline") coords '("c")))
(setq tap12 (ssadd (entlast) tap12))
(command "_mirror" (entlast) "" "3840,900" "3840,901" "No")
(setq tap12 (ssadd (entlast) tap12))
(setq coords (list 
(list 3840.4265 867.07) 
(list 3840.4157 867.07) 
(list 3840.4159 867.0803) 
(list 3840.4157 867.0906) 
(list 3840.4153 867.1008) 
(list 3840.4145 867.1111) 
(list 3840.4134 867.1214) 
(list 3840.412 867.1317) 
(list 3840.4104 867.1419) 
(list 3840.4086 867.1522) 
(list 3840.4066 867.1625) 
(list 3840.4045 867.1728) 
(list 3840.4024 867.1831) 
(list 3840.4004 867.1933) 
(list 3840.3984 867.2036) 
(list 3840.3967 867.2139) 
(list 3840.3952 867.2242) 
(list 3840.394 867.2344) 
(list 3840.3931 867.2447) 
(list 3840.3927 867.255) 
(list 3840.3927 867.2653) 
(list 3840.3931 867.2756) 
(list 3840.394 867.2858) 
(list 3840.3954 867.2961) 
(list 3840.3971 867.3064) 
(list 3840.3992 867.3167) 
(list 3840.4017 867.3269) 
(list 3840.4043 867.3372) 
(list 3840.4072 867.3475) 
(list 3840.4102 867.3578) 
(list 3840.4131 867.3681) 
(list 3840.416 867.3783) 
(list 3840.4187 867.3886) 
(list 3840.4211 867.3989) 
(list 3840.4231 867.4092) 
(list 3840.4248 867.4194) 
(list 3840.4259 867.4297) 
(list 3840.4265 867.44) 
(list 3840.4265 867.44)))
(apply 'command (append '("pline") coords '("c")))
(setq tap12 (ssadd (entlast) tap12))
(command "_mirror" (entlast) "" "3840,900" "3840,901" "No")
(setq tap12 (ssadd (entlast) tap12))
(setq coords (list 
(list 3841.132 867.07) 
(list 3840.4265 867.07) 
(list 3840.4265 867.0803) 
(list 3840.4265 867.0906) 
(list 3840.4265 867.1008) 
(list 3840.4265 867.1111) 
(list 3840.4265 867.1214) 
(list 3840.4265 867.1317) 
(list 3840.4265 867.1419) 
(list 3840.4265 867.1522) 
(list 3840.4265 867.1625) 
(list 3840.4265 867.1728) 
(list 3840.4265 867.1831) 
(list 3840.4265 867.1933) 
(list 3840.4265 867.2036) 
(list 3840.4265 867.2139) 
(list 3840.4265 867.2242) 
(list 3840.4265 867.2344) 
(list 3840.4265 867.2447) 
(list 3840.4265 867.255) 
(list 3840.4265 867.2653) 
(list 3840.4265 867.2756) 
(list 3840.4265 867.2858) 
(list 3840.4265 867.2961) 
(list 3840.4265 867.3064) 
(list 3840.4265 867.3167) 
(list 3840.4265 867.3269) 
(list 3840.4265 867.3372) 
(list 3840.4265 867.3475) 
(list 3840.4265 867.3578) 
(list 3840.4265 867.3681) 
(list 3840.4265 867.3783) 
(list 3840.4265 867.3886) 
(list 3840.4265 867.3989) 
(list 3840.4265 867.4092) 
(list 3840.4265 867.4194) 
(list 3840.4265 867.4297) 
(list 3840.4265 867.44) 
(list 3841.132 867.44)))
(apply 'command (append '("pline") coords '("c")))
(setq tap12 (ssadd (entlast) tap12))
(command "_mirror" (entlast) "" "3840,900" "3840,901" "No")
(setq tap12 (ssadd (entlast) tap12))
(setq coords (list 
(list 3840 867.44) 
(list 3840.125 867.44) 
(list 3840.125 867.4503) 
(list 3840.125 867.4606) 
(list 3840.125 867.4708) 
(list 3840.125 867.4811) 
(list 3840.125 867.4914) 
(list 3840.125 867.5017) 
(list 3840.125 867.5119) 
(list 3840.125 867.5222) 
(list 3840.125 867.5325) 
(list 3840.125 867.5428) 
(list 3840.125 867.5531) 
(list 3840.125 867.5633) 
(list 3840.125 867.5736) 
(list 3840.125 867.5839) 
(list 3840.125 867.5942) 
(list 3840.125 867.6044) 
(list 3840.125 867.6147) 
(list 3840.125 867.625) 
(list 3840.125 867.6353) 
(list 3840.125 867.6456) 
(list 3840.125 867.6558) 
(list 3840.125 867.6661) 
(list 3840.125 867.6764) 
(list 3840.125 867.6867) 
(list 3840.125 867.6969) 
(list 3840.125 867.7072) 
(list 3840.125 867.7175) 
(list 3840.125 867.7278) 
(list 3840.125 867.7381) 
(list 3840.125 867.7483) 
(list 3840.125 867.7586) 
(list 3840.125 867.7689) 
(list 3840.125 867.7792) 
(list 3840.125 867.7894) 
(list 3840.125 867.7997) 
(list 3840.125 867.81) 
(list 3840 867.81)))
(apply 'command (append '("pline") coords '("c")))
(setq tap12 (ssadd (entlast) tap12))
(command "_mirror" (entlast) "" "3840,900" "3840,901" "No")
(setq tap12 (ssadd (entlast) tap12))
(setq coords (list 
(list 3840.4372 867.44) 
(list 3840.4265 867.44) 
(list 3840.4265 867.4503) 
(list 3840.4259 867.4606) 
(list 3840.4247 867.4708) 
(list 3840.423 867.4811) 
(list 3840.4207 867.4914) 
(list 3840.418 867.5017) 
(list 3840.4149 867.5119) 
(list 3840.4115 867.5222) 
(list 3840.4079 867.5325) 
(list 3840.4041 867.5428) 
(list 3840.4005 867.5531) 
(list 3840.3969 867.5633) 
(list 3840.3936 867.5736) 
(list 3840.3907 867.5839) 
(list 3840.3882 867.5942) 
(list 3840.3864 867.6044) 
(list 3840.3851 867.6147) 
(list 3840.3845 867.625) 
(list 3840.3846 867.6353) 
(list 3840.3855 867.6456) 
(list 3840.3871 867.6558) 
(list 3840.3894 867.6661) 
(list 3840.3923 867.6764) 
(list 3840.3958 867.6867) 
(list 3840.3997 867.6969) 
(list 3840.404 867.7072) 
(list 3840.4085 867.7175) 
(list 3840.4131 867.7278) 
(list 3840.4176 867.7381) 
(list 3840.422 867.7483) 
(list 3840.426 867.7586) 
(list 3840.4296 867.7689) 
(list 3840.4326 867.7792) 
(list 3840.4349 867.7894) 
(list 3840.4365 867.7997) 
(list 3840.4372 867.81) 
(list 3840.4372 867.81)))
(apply 'command (append '("pline") coords '("c")))
(setq tap12 (ssadd (entlast) tap12))
(command "_mirror" (entlast) "" "3840,900" "3840,901" "No")
(setq tap12 (ssadd (entlast) tap12))
(setq coords (list 
(list 3841.132 867.44) 
(list 3840.4372 867.44) 
(list 3840.4372 867.4503) 
(list 3840.4372 867.4606) 
(list 3840.4372 867.4708) 
(list 3840.4372 867.4811) 
(list 3840.4372 867.4914) 
(list 3840.4372 867.5017) 
(list 3840.4372 867.5119) 
(list 3840.4372 867.5222) 
(list 3840.4372 867.5325) 
(list 3840.4372 867.5428) 
(list 3840.4372 867.5531) 
(list 3840.4372 867.5633) 
(list 3840.4372 867.5736) 
(list 3840.4372 867.5839) 
(list 3840.4372 867.5942) 
(list 3840.4372 867.6044) 
(list 3840.4372 867.6147) 
(list 3840.4372 867.625) 
(list 3840.4372 867.6353) 
(list 3840.4372 867.6456) 
(list 3840.4372 867.6558) 
(list 3840.4372 867.6661) 
(list 3840.4372 867.6764) 
(list 3840.4372 867.6867) 
(list 3840.4372 867.6969) 
(list 3840.4372 867.7072) 
(list 3840.4372 867.7175) 
(list 3840.4372 867.7278) 
(list 3840.4372 867.7381) 
(list 3840.4372 867.7483) 
(list 3840.4372 867.7586) 
(list 3840.4372 867.7689) 
(list 3840.4372 867.7792) 
(list 3840.4372 867.7894) 
(list 3840.4372 867.7997) 
(list 3840.4372 867.81) 
(list 3841.132 867.81)))
(apply 'command (append '("pline") coords '("c")))
(setq tap12 (ssadd (entlast) tap12))
(command "_mirror" (entlast) "" "3840,900" "3840,901" "No")
(setq tap12 (ssadd (entlast) tap12))
(setq coords (list 
(list 3840 867.81) 
(list 3840.125 867.81) 
(list 3840.125 867.8203) 
(list 3840.125 867.8306) 
(list 3840.125 867.8408) 
(list 3840.125 867.8511) 
(list 3840.125 867.8614) 
(list 3840.125 867.8717) 
(list 3840.125 867.8819) 
(list 3840.125 867.8922) 
(list 3840.125 867.9025) 
(list 3840.125 867.9128) 
(list 3840.125 867.9231) 
(list 3840.125 867.9333) 
(list 3840.125 867.9436) 
(list 3840.125 867.9539) 
(list 3840.125 867.9642) 
(list 3840.125 867.9744) 
(list 3840.125 867.9847) 
(list 3840.125 867.995) 
(list 3840.125 868.0053) 
(list 3840.125 868.0156) 
(list 3840.125 868.0258) 
(list 3840.125 868.0361) 
(list 3840.125 868.0464) 
(list 3840.125 868.0567) 
(list 3840.125 868.0669) 
(list 3840.125 868.0772) 
(list 3840.125 868.0875) 
(list 3840.125 868.0978) 
(list 3840.125 868.1081) 
(list 3840.125 868.1183) 
(list 3840.125 868.1286) 
(list 3840.125 868.1389) 
(list 3840.125 868.1492) 
(list 3840.125 868.1594) 
(list 3840.125 868.1697) 
(list 3840.125 868.18) 
(list 3840 868.18)))
(apply 'command (append '("pline") coords '("c")))
(setq tap12 (ssadd (entlast) tap12))
(command "_mirror" (entlast) "" "3840,900" "3840,901" "No")
(setq tap12 (ssadd (entlast) tap12))
(setq coords (list 
(list 3840.4479 867.81) 
(list 3840.4372 867.81) 
(list 3840.4371 867.8203) 
(list 3840.4361 867.8306) 
(list 3840.4342 867.8408) 
(list 3840.4315 867.8511) 
(list 3840.4281 867.8614) 
(list 3840.424 867.8717) 
(list 3840.4194 867.8819) 
(list 3840.4144 867.8922) 
(list 3840.4091 867.9025) 
(list 3840.4038 867.9128) 
(list 3840.3985 867.9231) 
(list 3840.3934 867.9333) 
(list 3840.3888 867.9436) 
(list 3840.3847 867.9539) 
(list 3840.3813 867.9642) 
(list 3840.3787 867.9744) 
(list 3840.377 867.9847) 
(list 3840.3763 867.995) 
(list 3840.3766 868.0053) 
(list 3840.3779 868.0156) 
(list 3840.3802 868.0258) 
(list 3840.3834 868.0361) 
(list 3840.3875 868.0464) 
(list 3840.3923 868.0567) 
(list 3840.3977 868.0669) 
(list 3840.4036 868.0772) 
(list 3840.4097 868.0875) 
(list 3840.416 868.0978) 
(list 3840.4221 868.1081) 
(list 3840.428 868.1183) 
(list 3840.4334 868.1286) 
(list 3840.4381 868.1389) 
(list 3840.4421 868.1492) 
(list 3840.4451 868.1594) 
(list 3840.4471 868.1697) 
(list 3840.4479 868.18) 
(list 3840.4479 868.18)))
(apply 'command (append '("pline") coords '("c")))
(setq tap12 (ssadd (entlast) tap12))
(command "_mirror" (entlast) "" "3840,900" "3840,901" "No")
(setq tap12 (ssadd (entlast) tap12))
(setq coords (list 
(list 3841.132 867.81) 
(list 3840.4479 867.81) 
(list 3840.4479 867.8203) 
(list 3840.4479 867.8306) 
(list 3840.4479 867.8408) 
(list 3840.4479 867.8511) 
(list 3840.4479 867.8614) 
(list 3840.4479 867.8717) 
(list 3840.4479 867.8819) 
(list 3840.4479 867.8922) 
(list 3840.4479 867.9025) 
(list 3840.4479 867.9128) 
(list 3840.4479 867.9231) 
(list 3840.4479 867.9333) 
(list 3840.4479 867.9436) 
(list 3840.4479 867.9539) 
(list 3840.4479 867.9642) 
(list 3840.4479 867.9744) 
(list 3840.4479 867.9847) 
(list 3840.4479 867.995) 
(list 3840.4479 868.0053) 
(list 3840.4479 868.0156) 
(list 3840.4479 868.0258) 
(list 3840.4479 868.0361) 
(list 3840.4479 868.0464) 
(list 3840.4479 868.0567) 
(list 3840.4479 868.0669) 
(list 3840.4479 868.0772) 
(list 3840.4479 868.0875) 
(list 3840.4479 868.0978) 
(list 3840.4479 868.1081) 
(list 3840.4479 868.1183) 
(list 3840.4479 868.1286) 
(list 3840.4479 868.1389) 
(list 3840.4479 868.1492) 
(list 3840.4479 868.1594) 
(list 3840.4479 868.1697) 
(list 3840.4479 868.18) 
(list 3841.132 868.18)))
(apply 'command (append '("pline") coords '("c")))
(setq tap12 (ssadd (entlast) tap12))
(command "_mirror" (entlast) "" "3840,900" "3840,901" "No")
(setq tap12 (ssadd (entlast) tap12))
(setq coords (list 
(list 3840 868.18) 
(list 3840.125 868.18) 
(list 3840.125 868.1903) 
(list 3840.125 868.2006) 
(list 3840.125 868.2108) 
(list 3840.125 868.2211) 
(list 3840.125 868.2314) 
(list 3840.125 868.2417) 
(list 3840.125 868.2519) 
(list 3840.125 868.2622) 
(list 3840.125 868.2725) 
(list 3840.125 868.2828) 
(list 3840.125 868.2931) 
(list 3840.125 868.3033) 
(list 3840.125 868.3136) 
(list 3840.125 868.3239) 
(list 3840.125 868.3342) 
(list 3840.125 868.3444) 
(list 3840.125 868.3547) 
(list 3840.125 868.365) 
(list 3840.125 868.3753) 
(list 3840.125 868.3856) 
(list 3840.125 868.3958) 
(list 3840.125 868.4061) 
(list 3840.125 868.4164) 
(list 3840.125 868.4267) 
(list 3840.125 868.4369) 
(list 3840.125 868.4472) 
(list 3840.125 868.4575) 
(list 3840.125 868.4678) 
(list 3840.125 868.4781) 
(list 3840.125 868.4883) 
(list 3840.125 868.4986) 
(list 3840.125 868.5089) 
(list 3840.125 868.5192) 
(list 3840.125 868.5294) 
(list 3840.125 868.5397) 
(list 3840.125 868.55) 
(list 3840 868.55)))
(apply 'command (append '("pline") coords '("c")))
(setq tap12 (ssadd (entlast) tap12))
(command "_mirror" (entlast) "" "3840,900" "3840,901" "No")
(setq tap12 (ssadd (entlast) tap12))
(setq coords (list 
(list 3840.4587 868.18) 
(list 3840.4479 868.18) 
(list 3840.4477 868.1903) 
(list 3840.4462 868.2006) 
(list 3840.4436 868.2108) 
(list 3840.44 868.2211) 
(list 3840.4354 868.2314) 
(list 3840.43 868.2417) 
(list 3840.4239 868.2519) 
(list 3840.4173 868.2622) 
(list 3840.4104 868.2725) 
(list 3840.4034 868.2828) 
(list 3840.3965 868.2931) 
(list 3840.39 868.3033) 
(list 3840.384 868.3136) 
(list 3840.3787 868.3239) 
(list 3840.3744 868.3342) 
(list 3840.3711 868.3444) 
(list 3840.369 868.3547) 
(list 3840.3681 868.365) 
(list 3840.3685 868.3753) 
(list 3840.3702 868.3856) 
(list 3840.3732 868.3958) 
(list 3840.3774 868.4061) 
(list 3840.3826 868.4164) 
(list 3840.3888 868.4267) 
(list 3840.3957 868.4369) 
(list 3840.4032 868.4472) 
(list 3840.411 868.4575) 
(list 3840.4189 868.4678) 
(list 3840.4266 868.4781) 
(list 3840.434 868.4883) 
(list 3840.4407 868.4986) 
(list 3840.4466 868.5089) 
(list 3840.4515 868.5192) 
(list 3840.4552 868.5294) 
(list 3840.4577 868.5397) 
(list 3840.4587 868.55) 
(list 3840.4587 868.55)))
(apply 'command (append '("pline") coords '("c")))
(setq tap12 (ssadd (entlast) tap12))
(command "_mirror" (entlast) "" "3840,900" "3840,901" "No")
(setq tap12 (ssadd (entlast) tap12))
(setq coords (list 
(list 3841.132 868.18) 
(list 3840.4587 868.18) 
(list 3840.4587 868.1903) 
(list 3840.4587 868.2006) 
(list 3840.4587 868.2108) 
(list 3840.4587 868.2211) 
(list 3840.4587 868.2314) 
(list 3840.4587 868.2417) 
(list 3840.4587 868.2519) 
(list 3840.4587 868.2622) 
(list 3840.4587 868.2725) 
(list 3840.4587 868.2828) 
(list 3840.4587 868.2931) 
(list 3840.4587 868.3033) 
(list 3840.4587 868.3136) 
(list 3840.4587 868.3239) 
(list 3840.4587 868.3342) 
(list 3840.4587 868.3444) 
(list 3840.4587 868.3547) 
(list 3840.4587 868.365) 
(list 3840.4587 868.3753) 
(list 3840.4587 868.3856) 
(list 3840.4587 868.3958) 
(list 3840.4587 868.4061) 
(list 3840.4587 868.4164) 
(list 3840.4587 868.4267) 
(list 3840.4587 868.4369) 
(list 3840.4587 868.4472) 
(list 3840.4587 868.4575) 
(list 3840.4587 868.4678) 
(list 3840.4587 868.4781) 
(list 3840.4587 868.4883) 
(list 3840.4587 868.4986) 
(list 3840.4587 868.5089) 
(list 3840.4587 868.5192) 
(list 3840.4587 868.5294) 
(list 3840.4587 868.5397) 
(list 3840.4587 868.55) 
(list 3841.132 868.55)))
(apply 'command (append '("pline") coords '("c")))
(setq tap12 (ssadd (entlast) tap12))
(command "_mirror" (entlast) "" "3840,900" "3840,901" "No")
(setq tap12 (ssadd (entlast) tap12))
(setq coords (list 
(list 3840 868.55) 
(list 3840.125 868.55) 
(list 3840.125 868.5603) 
(list 3840.125 868.5706) 
(list 3840.125 868.5808) 
(list 3840.125 868.5911) 
(list 3840.125 868.6014) 
(list 3840.125 868.6117) 
(list 3840.125 868.6219) 
(list 3840.125 868.6322) 
(list 3840.125 868.6425) 
(list 3840.125 868.6528) 
(list 3840.125 868.6631) 
(list 3840.125 868.6733) 
(list 3840.125 868.6836) 
(list 3840.125 868.6939) 
(list 3840.125 868.7042) 
(list 3840.125 868.7144) 
(list 3840.125 868.7247) 
(list 3840.125 868.735) 
(list 3840.125 868.7453) 
(list 3840.125 868.7556) 
(list 3840.125 868.7658) 
(list 3840.125 868.7761) 
(list 3840.125 868.7864) 
(list 3840.125 868.7967) 
(list 3840.125 868.8069) 
(list 3840.125 868.8172) 
(list 3840.125 868.8275) 
(list 3840.125 868.8378) 
(list 3840.125 868.8481) 
(list 3840.125 868.8583) 
(list 3840.125 868.8686) 
(list 3840.125 868.8789) 
(list 3840.125 868.8892) 
(list 3840.125 868.8994) 
(list 3840.125 868.9097) 
(list 3840.125 868.92) 
(list 3840 868.92)))
(apply 'command (append '("pline") coords '("c")))
(setq tap12 (ssadd (entlast) tap12))
(command "_mirror" (entlast) "" "3840,900" "3840,901" "No")
(setq tap12 (ssadd (entlast) tap12))
(setq coords (list 
(list 3840.4694 868.55) 
(list 3840.4587 868.55) 
(list 3840.4582 868.5603) 
(list 3840.4564 868.5706) 
(list 3840.4531 868.5808) 
(list 3840.4485 868.5911) 
(list 3840.4428 868.6014) 
(list 3840.436 868.6117) 
(list 3840.4284 868.6219) 
(list 3840.4202 868.6322) 
(list 3840.4117 868.6425) 
(list 3840.403 868.6528) 
(list 3840.3945 868.6631) 
(list 3840.3865 868.6733) 
(list 3840.3792 868.6836) 
(list 3840.3727 868.6939) 
(list 3840.3675 868.7042) 
(list 3840.3635 868.7144) 
(list 3840.3609 868.7247) 
(list 3840.3599 868.735) 
(list 3840.3605 868.7453) 
(list 3840.3626 868.7556) 
(list 3840.3663 868.7658) 
(list 3840.3714 868.7761) 
(list 3840.3778 868.7864) 
(list 3840.3854 868.7967) 
(list 3840.3938 868.8069) 
(list 3840.4028 868.8172) 
(list 3840.4123 868.8275) 
(list 3840.4218 868.8378) 
(list 3840.4312 868.8481) 
(list 3840.44 868.8583) 
(list 3840.4481 868.8686) 
(list 3840.4552 868.8789) 
(list 3840.461 868.8892) 
(list 3840.4654 868.8994) 
(list 3840.4682 868.9097) 
(list 3840.4694 868.92) 
(list 3840.4694 868.92)))
(apply 'command (append '("pline") coords '("c")))
(setq tap12 (ssadd (entlast) tap12))
(command "_mirror" (entlast) "" "3840,900" "3840,901" "No")
(setq tap12 (ssadd (entlast) tap12))
(setq coords (list 
(list 3841.132 868.55) 
(list 3840.4694 868.55) 
(list 3840.4694 868.5603) 
(list 3840.4694 868.5706) 
(list 3840.4694 868.5808) 
(list 3840.4694 868.5911) 
(list 3840.4694 868.6014) 
(list 3840.4694 868.6117) 
(list 3840.4694 868.6219) 
(list 3840.4694 868.6322) 
(list 3840.4694 868.6425) 
(list 3840.4694 868.6528) 
(list 3840.4694 868.6631) 
(list 3840.4694 868.6733) 
(list 3840.4694 868.6836) 
(list 3840.4694 868.6939) 
(list 3840.4694 868.7042) 
(list 3840.4694 868.7144) 
(list 3840.4694 868.7247) 
(list 3840.4694 868.735) 
(list 3840.4694 868.7453) 
(list 3840.4694 868.7556) 
(list 3840.4694 868.7658) 
(list 3840.4694 868.7761) 
(list 3840.4694 868.7864) 
(list 3840.4694 868.7967) 
(list 3840.4694 868.8069) 
(list 3840.4694 868.8172) 
(list 3840.4694 868.8275) 
(list 3840.4694 868.8378) 
(list 3840.4694 868.8481) 
(list 3840.4694 868.8583) 
(list 3840.4694 868.8686) 
(list 3840.4694 868.8789) 
(list 3840.4694 868.8892) 
(list 3840.4694 868.8994) 
(list 3840.4694 868.9097) 
(list 3840.4694 868.92) 
(list 3841.132 868.92)))
(apply 'command (append '("pline") coords '("c")))
(setq tap12 (ssadd (entlast) tap12))
(command "_mirror" (entlast) "" "3840,900" "3840,901" "No")
(setq tap12 (ssadd (entlast) tap12))
(setq coords (list 
(list 3840 868.92) 
(list 3840.125 868.92) 
(list 3840.125 868.9303) 
(list 3840.125 868.9406) 
(list 3840.125 868.9508) 
(list 3840.125 868.9611) 
(list 3840.125 868.9714) 
(list 3840.125 868.9817) 
(list 3840.125 868.9919) 
(list 3840.125 869.0022) 
(list 3840.125 869.0125) 
(list 3840.125 869.0228) 
(list 3840.125 869.0331) 
(list 3840.125 869.0433) 
(list 3840.125 869.0536) 
(list 3840.125 869.0639) 
(list 3840.125 869.0742) 
(list 3840.125 869.0844) 
(list 3840.125 869.0947) 
(list 3840.125 869.105) 
(list 3840.125 869.1153) 
(list 3840.125 869.1256) 
(list 3840.125 869.1358) 
(list 3840.125 869.1461) 
(list 3840.125 869.1564) 
(list 3840.125 869.1667) 
(list 3840.125 869.1769) 
(list 3840.125 869.1872) 
(list 3840.125 869.1975) 
(list 3840.125 869.2078) 
(list 3840.125 869.2181) 
(list 3840.125 869.2283) 
(list 3840.125 869.2386) 
(list 3840.125 869.2489) 
(list 3840.125 869.2592) 
(list 3840.125 869.2694) 
(list 3840.125 869.2797) 
(list 3840.125 869.29) 
(list 3840 869.29)))
(apply 'command (append '("pline") coords '("c")))
(setq tap12 (ssadd (entlast) tap12))
(command "_mirror" (entlast) "" "3840,900" "3840,901" "No")
(setq tap12 (ssadd (entlast) tap12))
(setq coords (list 
(list 3840.4801 868.92) 
(list 3840.4694 868.92) 
(list 3840.4688 868.9303) 
(list 3840.4665 868.9406) 
(list 3840.4626 868.9508) 
(list 3840.4571 868.9611) 
(list 3840.4501 868.9714) 
(list 3840.442 868.9817) 
(list 3840.4329 868.9919) 
(list 3840.4231 869.0022) 
(list 3840.4129 869.0125) 
(list 3840.4026 869.0228) 
(list 3840.3926 869.0331) 
(list 3840.383 869.0433) 
(list 3840.3744 869.0536) 
(list 3840.3668 869.0639) 
(list 3840.3605 869.0742) 
(list 3840.3558 869.0844) 
(list 3840.3529 869.0947) 
(list 3840.3517 869.105) 
(list 3840.3524 869.1153) 
(list 3840.355 869.1256) 
(list 3840.3594 869.1358) 
(list 3840.3654 869.1461) 
(list 3840.373 869.1564) 
(list 3840.3819 869.1667) 
(list 3840.3918 869.1769) 
(list 3840.4025 869.1872) 
(list 3840.4136 869.1975) 
(list 3840.4247 869.2078) 
(list 3840.4357 869.2181) 
(list 3840.446 869.2283) 
(list 3840.4554 869.2386) 
(list 3840.4637 869.2489) 
(list 3840.4705 869.2592) 
(list 3840.4756 869.2694) 
(list 3840.4788 869.2797) 
(list 3840.4801 869.29) 
(list 3840.4801 869.29)))
(apply 'command (append '("pline") coords '("c")))
(setq tap12 (ssadd (entlast) tap12))
(command "_mirror" (entlast) "" "3840,900" "3840,901" "No")
(setq tap12 (ssadd (entlast) tap12))
(setq coords (list 
(list 3841.132 868.92) 
(list 3840.4801 868.92) 
(list 3840.4801 868.9303) 
(list 3840.4801 868.9406) 
(list 3840.4801 868.9508) 
(list 3840.4801 868.9611) 
(list 3840.4801 868.9714) 
(list 3840.4801 868.9817) 
(list 3840.4801 868.9919) 
(list 3840.4801 869.0022) 
(list 3840.4801 869.0125) 
(list 3840.4801 869.0228) 
(list 3840.4801 869.0331) 
(list 3840.4801 869.0433) 
(list 3840.4801 869.0536) 
(list 3840.4801 869.0639) 
(list 3840.4801 869.0742) 
(list 3840.4801 869.0844) 
(list 3840.4801 869.0947) 
(list 3840.4801 869.105) 
(list 3840.4801 869.1153) 
(list 3840.4801 869.1256) 
(list 3840.4801 869.1358) 
(list 3840.4801 869.1461) 
(list 3840.4801 869.1564) 
(list 3840.4801 869.1667) 
(list 3840.4801 869.1769) 
(list 3840.4801 869.1872) 
(list 3840.4801 869.1975) 
(list 3840.4801 869.2078) 
(list 3840.4801 869.2181) 
(list 3840.4801 869.2283) 
(list 3840.4801 869.2386) 
(list 3840.4801 869.2489) 
(list 3840.4801 869.2592) 
(list 3840.4801 869.2694) 
(list 3840.4801 869.2797) 
(list 3840.4801 869.29) 
(list 3841.132 869.29)))
(apply 'command (append '("pline") coords '("c")))
(setq tap12 (ssadd (entlast) tap12))
(command "_mirror" (entlast) "" "3840,900" "3840,901" "No")
(setq tap12 (ssadd (entlast) tap12))
(setq coords (list 
(list 3840 869.29) 
(list 3840.125 869.29) 
(list 3840.125 869.3003) 
(list 3840.125 869.3106) 
(list 3840.125 869.3208) 
(list 3840.125 869.3311) 
(list 3840.125 869.3414) 
(list 3840.125 869.3517) 
(list 3840.125 869.3619) 
(list 3840.125 869.3722) 
(list 3840.125 869.3825) 
(list 3840.125 869.3928) 
(list 3840.125 869.4031) 
(list 3840.125 869.4133) 
(list 3840.125 869.4236) 
(list 3840.125 869.4339) 
(list 3840.125 869.4442) 
(list 3840.125 869.4544) 
(list 3840.125 869.4647) 
(list 3840.125 869.475) 
(list 3840.125 869.4853) 
(list 3840.125 869.4956) 
(list 3840.125 869.5058) 
(list 3840.125 869.5161) 
(list 3840.125 869.5264) 
(list 3840.125 869.5367) 
(list 3840.125 869.5469) 
(list 3840.125 869.5572) 
(list 3840.125 869.5675) 
(list 3840.125 869.5778) 
(list 3840.125 869.5881) 
(list 3840.125 869.5983) 
(list 3840.125 869.6086) 
(list 3840.125 869.6189) 
(list 3840.125 869.6292) 
(list 3840.125 869.6394) 
(list 3840.125 869.6497) 
(list 3840.125 869.66) 
(list 3840 869.66)))
(apply 'command (append '("pline") coords '("c")))
(setq tap12 (ssadd (entlast) tap12))
(command "_mirror" (entlast) "" "3840,900" "3840,901" "No")
(setq tap12 (ssadd (entlast) tap12))
(setq coords (list 
(list 3840.4909 869.29) 
(list 3840.4801 869.29) 
(list 3840.4794 869.3003) 
(list 3840.4767 869.3106) 
(list 3840.472 869.3208) 
(list 3840.4656 869.3311) 
(list 3840.4575 869.3414) 
(list 3840.448 869.3517) 
(list 3840.4374 869.3619) 
(list 3840.426 869.3722) 
(list 3840.4142 869.3825) 
(list 3840.4023 869.3928) 
(list 3840.3906 869.4031) 
(list 3840.3796 869.4133) 
(list 3840.3695 869.4236) 
(list 3840.3608 869.4339) 
(list 3840.3536 869.4442) 
(list 3840.3482 869.4544) 
(list 3840.3448 869.4647) 
(list 3840.3435 869.475) 
(list 3840.3444 869.4853) 
(list 3840.3474 869.4956) 
(list 3840.3524 869.5058) 
(list 3840.3594 869.5161) 
(list 3840.3682 869.5264) 
(list 3840.3784 869.5367) 
(list 3840.3898 869.5469) 
(list 3840.4021 869.5572) 
(list 3840.4148 869.5675) 
(list 3840.4276 869.5778) 
(list 3840.4402 869.5881) 
(list 3840.452 869.5983) 
(list 3840.4628 869.6086) 
(list 3840.4722 869.6189) 
(list 3840.4799 869.6292) 
(list 3840.4857 869.6394) 
(list 3840.4894 869.6497) 
(list 3840.4909 869.66) 
(list 3840.4909 869.66)))
(apply 'command (append '("pline") coords '("c")))
(setq tap12 (ssadd (entlast) tap12))
(command "_mirror" (entlast) "" "3840,900" "3840,901" "No")
(setq tap12 (ssadd (entlast) tap12))
(setq coords (list 
(list 3841.132 869.29) 
(list 3840.4909 869.29) 
(list 3840.4909 869.3003) 
(list 3840.4909 869.3106) 
(list 3840.4909 869.3208) 
(list 3840.4909 869.3311) 
(list 3840.4909 869.3414) 
(list 3840.4909 869.3517) 
(list 3840.4909 869.3619) 
(list 3840.4909 869.3722) 
(list 3840.4909 869.3825) 
(list 3840.4909 869.3928) 
(list 3840.4909 869.4031) 
(list 3840.4909 869.4133) 
(list 3840.4909 869.4236) 
(list 3840.4909 869.4339) 
(list 3840.4909 869.4442) 
(list 3840.4909 869.4544) 
(list 3840.4909 869.4647) 
(list 3840.4909 869.475) 
(list 3840.4909 869.4853) 
(list 3840.4909 869.4956) 
(list 3840.4909 869.5058) 
(list 3840.4909 869.5161) 
(list 3840.4909 869.5264) 
(list 3840.4909 869.5367) 
(list 3840.4909 869.5469) 
(list 3840.4909 869.5572) 
(list 3840.4909 869.5675) 
(list 3840.4909 869.5778) 
(list 3840.4909 869.5881) 
(list 3840.4909 869.5983) 
(list 3840.4909 869.6086) 
(list 3840.4909 869.6189) 
(list 3840.4909 869.6292) 
(list 3840.4909 869.6394) 
(list 3840.4909 869.6497) 
(list 3840.4909 869.66) 
(list 3841.132 869.66)))
(apply 'command (append '("pline") coords '("c")))
(setq tap12 (ssadd (entlast) tap12))
(command "_mirror" (entlast) "" "3840,900" "3840,901" "No")
(setq tap12 (ssadd (entlast) tap12))
(setq coords (list 
(list 3840 869.66) 
(list 3840.125 869.66) 
(list 3840.125 869.6703) 
(list 3840.125 869.6806) 
(list 3840.125 869.6908) 
(list 3840.125 869.7011) 
(list 3840.125 869.7114) 
(list 3840.125 869.7217) 
(list 3840.125 869.7319) 
(list 3840.125 869.7422) 
(list 3840.125 869.7525) 
(list 3840.125 869.7628) 
(list 3840.125 869.7731) 
(list 3840.125 869.7833) 
(list 3840.125 869.7936) 
(list 3840.125 869.8039) 
(list 3840.125 869.8142) 
(list 3840.125 869.8244) 
(list 3840.125 869.8347) 
(list 3840.125 869.845) 
(list 3840.125 869.8553) 
(list 3840.125 869.8656) 
(list 3840.125 869.8758) 
(list 3840.125 869.8861) 
(list 3840.125 869.8964) 
(list 3840.125 869.9067) 
(list 3840.125 869.9169) 
(list 3840.125 869.9272) 
(list 3840.125 869.9375) 
(list 3840.125 869.9478) 
(list 3840.125 869.9581) 
(list 3840.125 869.9683) 
(list 3840.125 869.9786) 
(list 3840.125 869.9889) 
(list 3840.125 869.9992) 
(list 3840.125 870.0094) 
(list 3840.125 870.0197) 
(list 3840.125 870.03) 
(list 3840 870.03)))
(apply 'command (append '("pline") coords '("c")))
(setq tap12 (ssadd (entlast) tap12))
(command "_mirror" (entlast) "" "3840,900" "3840,901" "No")
(setq tap12 (ssadd (entlast) tap12))
(setq coords (list 
(list 3840.5016 869.66) 
(list 3840.4909 869.66) 
(list 3840.49 869.6703) 
(list 3840.4869 869.6806) 
(list 3840.4815 869.6908) 
(list 3840.4741 869.7011) 
(list 3840.4648 869.7114) 
(list 3840.454 869.7217) 
(list 3840.4419 869.7319) 
(list 3840.4289 869.7422) 
(list 3840.4154 869.7525) 
(list 3840.4019 869.7628) 
(list 3840.3886 869.7731) 
(list 3840.3761 869.7833) 
(list 3840.3647 869.7936) 
(list 3840.3548 869.8039) 
(list 3840.3467 869.8142) 
(list 3840.3406 869.8244) 
(list 3840.3367 869.8347) 
(list 3840.3353 869.845) 
(list 3840.3363 869.8553) 
(list 3840.3397 869.8656) 
(list 3840.3455 869.8758) 
(list 3840.3535 869.8861) 
(list 3840.3634 869.8964) 
(list 3840.375 869.9067) 
(list 3840.3879 869.9169) 
(list 3840.4017 869.9272) 
(list 3840.4161 869.9375) 
(list 3840.4305 869.9478) 
(list 3840.4447 869.9581) 
(list 3840.458 869.9683) 
(list 3840.4701 869.9786) 
(list 3840.4807 869.9889) 
(list 3840.4894 869.9992) 
(list 3840.4959 870.0094) 
(list 3840.5 870.0197) 
(list 3840.5016 870.03) 
(list 3840.5016 870.03)))
(apply 'command (append '("pline") coords '("c")))
(setq tap12 (ssadd (entlast) tap12))
(command "_mirror" (entlast) "" "3840,900" "3840,901" "No")
(setq tap12 (ssadd (entlast) tap12))
(setq coords (list 
(list 3841.132 869.66) 
(list 3840.5016 869.66) 
(list 3840.5016 869.6703) 
(list 3840.5016 869.6806) 
(list 3840.5016 869.6908) 
(list 3840.5016 869.7011) 
(list 3840.5016 869.7114) 
(list 3840.5016 869.7217) 
(list 3840.5016 869.7319) 
(list 3840.5016 869.7422) 
(list 3840.5016 869.7525) 
(list 3840.5016 869.7628) 
(list 3840.5016 869.7731) 
(list 3840.5016 869.7833) 
(list 3840.5016 869.7936) 
(list 3840.5016 869.8039) 
(list 3840.5016 869.8142) 
(list 3840.5016 869.8244) 
(list 3840.5016 869.8347) 
(list 3840.5016 869.845) 
(list 3840.5016 869.8553) 
(list 3840.5016 869.8656) 
(list 3840.5016 869.8758) 
(list 3840.5016 869.8861) 
(list 3840.5016 869.8964) 
(list 3840.5016 869.9067) 
(list 3840.5016 869.9169) 
(list 3840.5016 869.9272) 
(list 3840.5016 869.9375) 
(list 3840.5016 869.9478) 
(list 3840.5016 869.9581) 
(list 3840.5016 869.9683) 
(list 3840.5016 869.9786) 
(list 3840.5016 869.9889) 
(list 3840.5016 869.9992) 
(list 3840.5016 870.0094) 
(list 3840.5016 870.0197) 
(list 3840.5016 870.03) 
(list 3841.132 870.03)))
(apply 'command (append '("pline") coords '("c")))
(setq tap12 (ssadd (entlast) tap12))
(command "_mirror" (entlast) "" "3840,900" "3840,901" "No")
(setq tap12 (ssadd (entlast) tap12))
(setq coords (list 
(list 3840 870.03) 
(list 3840.125 870.03) 
(list 3840.125 870.0403) 
(list 3840.125 870.0506) 
(list 3840.125 870.0608) 
(list 3840.125 870.0711) 
(list 3840.125 870.0814) 
(list 3840.125 870.0917) 
(list 3840.125 870.1019) 
(list 3840.125 870.1122) 
(list 3840.125 870.1225) 
(list 3840.125 870.1328) 
(list 3840.125 870.1431) 
(list 3840.125 870.1533) 
(list 3840.125 870.1636) 
(list 3840.125 870.1739) 
(list 3840.125 870.1842) 
(list 3840.125 870.1944) 
(list 3840.125 870.2047) 
(list 3840.125 870.215) 
(list 3840.125 870.2253) 
(list 3840.125 870.2356) 
(list 3840.125 870.2458) 
(list 3840.125 870.2561) 
(list 3840.125 870.2664) 
(list 3840.125 870.2767) 
(list 3840.125 870.2869) 
(list 3840.125 870.2972) 
(list 3840.125 870.3075) 
(list 3840.125 870.3178) 
(list 3840.125 870.3281) 
(list 3840.125 870.3383) 
(list 3840.125 870.3486) 
(list 3840.125 870.3589) 
(list 3840.125 870.3692) 
(list 3840.125 870.3794) 
(list 3840.125 870.3897) 
(list 3840.125 870.4) 
(list 3840 870.4)))
(apply 'command (append '("pline") coords '("c")))
(setq tap12 (ssadd (entlast) tap12))
(command "_mirror" (entlast) "" "3840,900" "3840,901" "No")
(setq tap12 (ssadd (entlast) tap12))
(setq coords (list 
(list 3840.5123 870.03) 
(list 3840.5016 870.03) 
(list 3840.5006 870.0403) 
(list 3840.497 870.0506) 
(list 3840.491 870.0608) 
(list 3840.4826 870.0711) 
(list 3840.4722 870.0814) 
(list 3840.46 870.0917) 
(list 3840.4464 870.1019) 
(list 3840.4318 870.1122) 
(list 3840.4167 870.1225) 
(list 3840.4015 870.1328) 
(list 3840.3867 870.1431) 
(list 3840.3726 870.1533) 
(list 3840.3599 870.1636) 
(list 3840.3488 870.1739) 
(list 3840.3397 870.1842) 
(list 3840.3329 870.1944) 
(list 3840.3287 870.2047) 
(list 3840.3271 870.215) 
(list 3840.3282 870.2253) 
(list 3840.3321 870.2356) 
(list 3840.3386 870.2458) 
(list 3840.3475 870.2561) 
(list 3840.3586 870.2664) 
(list 3840.3715 870.2767) 
(list 3840.3859 870.2869) 
(list 3840.4013 870.2972) 
(list 3840.4174 870.3075) 
(list 3840.4335 870.3178) 
(list 3840.4492 870.3281) 
(list 3840.464 870.3383) 
(list 3840.4775 870.3486) 
(list 3840.4892 870.3589) 
(list 3840.4989 870.3692) 
(list 3840.5061 870.3794) 
(list 3840.5106 870.3897) 
(list 3840.5123 870.4) 
(list 3840.5123 870.4)))
(apply 'command (append '("pline") coords '("c")))
(setq tap12 (ssadd (entlast) tap12))
(command "_mirror" (entlast) "" "3840,900" "3840,901" "No")
(setq tap12 (ssadd (entlast) tap12))
(setq coords (list 
(list 3841.132 870.03) 
(list 3840.5123 870.03) 
(list 3840.5123 870.0403) 
(list 3840.5123 870.0506) 
(list 3840.5123 870.0608) 
(list 3840.5123 870.0711) 
(list 3840.5123 870.0814) 
(list 3840.5123 870.0917) 
(list 3840.5123 870.1019) 
(list 3840.5123 870.1122) 
(list 3840.5123 870.1225) 
(list 3840.5123 870.1328) 
(list 3840.5123 870.1431) 
(list 3840.5123 870.1533) 
(list 3840.5123 870.1636) 
(list 3840.5123 870.1739) 
(list 3840.5123 870.1842) 
(list 3840.5123 870.1944) 
(list 3840.5123 870.2047) 
(list 3840.5123 870.215) 
(list 3840.5123 870.2253) 
(list 3840.5123 870.2356) 
(list 3840.5123 870.2458) 
(list 3840.5123 870.2561) 
(list 3840.5123 870.2664) 
(list 3840.5123 870.2767) 
(list 3840.5123 870.2869) 
(list 3840.5123 870.2972) 
(list 3840.5123 870.3075) 
(list 3840.5123 870.3178) 
(list 3840.5123 870.3281) 
(list 3840.5123 870.3383) 
(list 3840.5123 870.3486) 
(list 3840.5123 870.3589) 
(list 3840.5123 870.3692) 
(list 3840.5123 870.3794) 
(list 3840.5123 870.3897) 
(list 3840.5123 870.4) 
(list 3841.132 870.4)))
(apply 'command (append '("pline") coords '("c")))
(setq tap12 (ssadd (entlast) tap12))
(command "_mirror" (entlast) "" "3840,900" "3840,901" "No")
(setq tap12 (ssadd (entlast) tap12))
(setq coords (list 
(list 3840 870.4) 
(list 3840.125 870.4) 
(list 3840.125 870.4103) 
(list 3840.125 870.4206) 
(list 3840.125 870.4308) 
(list 3840.125 870.4411) 
(list 3840.125 870.4514) 
(list 3840.125 870.4617) 
(list 3840.125 870.4719) 
(list 3840.125 870.4822) 
(list 3840.125 870.4925) 
(list 3840.125 870.5028) 
(list 3840.125 870.5131) 
(list 3840.125 870.5233) 
(list 3840.125 870.5336) 
(list 3840.125 870.5439) 
(list 3840.125 870.5542) 
(list 3840.125 870.5644) 
(list 3840.125 870.5747) 
(list 3840.125 870.585) 
(list 3840.125 870.5953) 
(list 3840.125 870.6056) 
(list 3840.125 870.6158) 
(list 3840.125 870.6261) 
(list 3840.125 870.6364) 
(list 3840.125 870.6467) 
(list 3840.125 870.6569) 
(list 3840.125 870.6672) 
(list 3840.125 870.6775) 
(list 3840.125 870.6878) 
(list 3840.125 870.6981) 
(list 3840.125 870.7083) 
(list 3840.125 870.7186) 
(list 3840.125 870.7289) 
(list 3840.125 870.7392) 
(list 3840.125 870.7494) 
(list 3840.125 870.7597) 
(list 3840.125 870.77) 
(list 3840 870.77)))
(apply 'command (append '("pline") coords '("c")))
(setq tap12 (ssadd (entlast) tap12))
(command "_mirror" (entlast) "" "3840,900" "3840,901" "No")
(setq tap12 (ssadd (entlast) tap12))
(setq coords (list 
(list 3840.5231 870.4) 
(list 3840.5123 870.4) 
(list 3840.5112 870.4103) 
(list 3840.5072 870.4206) 
(list 3840.5004 870.4308) 
(list 3840.4911 870.4411) 
(list 3840.4795 870.4514) 
(list 3840.466 870.4617) 
(list 3840.4509 870.4719) 
(list 3840.4348 870.4822) 
(list 3840.418 870.4925) 
(list 3840.4011 870.5028) 
(list 3840.3847 870.5131) 
(list 3840.3692 870.5233) 
(list 3840.3551 870.5336) 
(list 3840.3428 870.5439) 
(list 3840.3328 870.5542) 
(list 3840.3253 870.5644) 
(list 3840.3206 870.5747) 
(list 3840.3189 870.585) 
(list 3840.3202 870.5953) 
(list 3840.3245 870.6056) 
(list 3840.3316 870.6158) 
(list 3840.3415 870.6261) 
(list 3840.3537 870.6364) 
(list 3840.368 870.6467) 
(list 3840.3839 870.6569) 
(list 3840.401 870.6672) 
(list 3840.4186 870.6775) 
(list 3840.4364 870.6878) 
(list 3840.4537 870.6981) 
(list 3840.47 870.7083) 
(list 3840.4848 870.7186) 
(list 3840.4978 870.7289) 
(list 3840.5083 870.7392) 
(list 3840.5162 870.7494) 
(list 3840.5212 870.7597) 
(list 3840.5231 870.77) 
(list 3840.5231 870.77)))
(apply 'command (append '("pline") coords '("c")))
(setq tap12 (ssadd (entlast) tap12))
(command "_mirror" (entlast) "" "3840,900" "3840,901" "No")
(setq tap12 (ssadd (entlast) tap12))
(setq coords (list 
(list 3841.132 870.4) 
(list 3840.5231 870.4) 
(list 3840.5231 870.4103) 
(list 3840.5231 870.4206) 
(list 3840.5231 870.4308) 
(list 3840.5231 870.4411) 
(list 3840.5231 870.4514) 
(list 3840.5231 870.4617) 
(list 3840.5231 870.4719) 
(list 3840.5231 870.4822) 
(list 3840.5231 870.4925) 
(list 3840.5231 870.5028) 
(list 3840.5231 870.5131) 
(list 3840.5231 870.5233) 
(list 3840.5231 870.5336) 
(list 3840.5231 870.5439) 
(list 3840.5231 870.5542) 
(list 3840.5231 870.5644) 
(list 3840.5231 870.5747) 
(list 3840.5231 870.585) 
(list 3840.5231 870.5953) 
(list 3840.5231 870.6056) 
(list 3840.5231 870.6158) 
(list 3840.5231 870.6261) 
(list 3840.5231 870.6364) 
(list 3840.5231 870.6467) 
(list 3840.5231 870.6569) 
(list 3840.5231 870.6672) 
(list 3840.5231 870.6775) 
(list 3840.5231 870.6878) 
(list 3840.5231 870.6981) 
(list 3840.5231 870.7083) 
(list 3840.5231 870.7186) 
(list 3840.5231 870.7289) 
(list 3840.5231 870.7392) 
(list 3840.5231 870.7494) 
(list 3840.5231 870.7597) 
(list 3840.5231 870.77) 
(list 3841.132 870.77)))
(apply 'command (append '("pline") coords '("c")))
(setq tap12 (ssadd (entlast) tap12))
(command "_mirror" (entlast) "" "3840,900" "3840,901" "No")
(setq tap12 (ssadd (entlast) tap12))
(setq coords (list 
(list 3840 870.77) 
(list 3840.125 870.77) 
(list 3840.125 870.7803) 
(list 3840.125 870.7906) 
(list 3840.125 870.8008) 
(list 3840.125 870.8111) 
(list 3840.125 870.8214) 
(list 3840.125 870.8317) 
(list 3840.125 870.8419) 
(list 3840.125 870.8522) 
(list 3840.125 870.8625) 
(list 3840.125 870.8728) 
(list 3840.125 870.8831) 
(list 3840.125 870.8933) 
(list 3840.125 870.9036) 
(list 3840.125 870.9139) 
(list 3840.125 870.9242) 
(list 3840.125 870.9344) 
(list 3840.125 870.9447) 
(list 3840.125 870.955) 
(list 3840.125 870.9653) 
(list 3840.125 870.9756) 
(list 3840.125 870.9858) 
(list 3840.125 870.9961) 
(list 3840.125 871.0064) 
(list 3840.125 871.0167) 
(list 3840.125 871.0269) 
(list 3840.125 871.0372) 
(list 3840.125 871.0475) 
(list 3840.125 871.0578) 
(list 3840.125 871.0681) 
(list 3840.125 871.0783) 
(list 3840.125 871.0886) 
(list 3840.125 871.0989) 
(list 3840.125 871.1092) 
(list 3840.125 871.1194) 
(list 3840.125 871.1297) 
(list 3840.125 871.14) 
(list 3840 871.14)))
(apply 'command (append '("pline") coords '("c")))
(setq tap12 (ssadd (entlast) tap12))
(command "_mirror" (entlast) "" "3840,900" "3840,901" "No")
(setq tap12 (ssadd (entlast) tap12))
(setq coords (list 
(list 3840.5338 870.77) 
(list 3840.5231 870.77) 
(list 3840.5218 870.7803) 
(list 3840.5174 870.7906) 
(list 3840.5099 870.8008) 
(list 3840.4997 870.8111) 
(list 3840.4869 870.8214) 
(list 3840.472 870.8317) 
(list 3840.4554 870.8419) 
(list 3840.4377 870.8522) 
(list 3840.4192 870.8625) 
(list 3840.4007 870.8728) 
(list 3840.3827 870.8831) 
(list 3840.3657 870.8933) 
(list 3840.3503 870.9036) 
(list 3840.3368 870.9139) 
(list 3840.3259 870.9242) 
(list 3840.3177 870.9344) 
(list 3840.3126 870.9447) 
(list 3840.3107 870.955) 
(list 3840.3121 870.9653) 
(list 3840.3168 870.9756) 
(list 3840.3247 870.9858) 
(list 3840.3355 870.9961) 
(list 3840.3489 871.0064) 
(list 3840.3646 871.0167) 
(list 3840.3819 871.0269) 
(list 3840.4006 871.0372) 
(list 3840.4199 871.0475) 
(list 3840.4393 871.0578) 
(list 3840.4582 871.0681) 
(list 3840.476 871.0783) 
(list 3840.4922 871.0886) 
(list 3840.5063 871.0989) 
(list 3840.5178 871.1092) 
(list 3840.5264 871.1194) 
(list 3840.5318 871.1297) 
(list 3840.5338 871.14) 
(list 3840.5338 871.14)))
(apply 'command (append '("pline") coords '("c")))
(setq tap12 (ssadd (entlast) tap12))
(command "_mirror" (entlast) "" "3840,900" "3840,901" "No")
(setq tap12 (ssadd (entlast) tap12))
(setq coords (list 
(list 3841.132 870.77) 
(list 3840.5338 870.77) 
(list 3840.5338 870.7803) 
(list 3840.5338 870.7906) 
(list 3840.5338 870.8008) 
(list 3840.5338 870.8111) 
(list 3840.5338 870.8214) 
(list 3840.5338 870.8317) 
(list 3840.5338 870.8419) 
(list 3840.5338 870.8522) 
(list 3840.5338 870.8625) 
(list 3840.5338 870.8728) 
(list 3840.5338 870.8831) 
(list 3840.5338 870.8933) 
(list 3840.5338 870.9036) 
(list 3840.5338 870.9139) 
(list 3840.5338 870.9242) 
(list 3840.5338 870.9344) 
(list 3840.5338 870.9447) 
(list 3840.5338 870.955) 
(list 3840.5338 870.9653) 
(list 3840.5338 870.9756) 
(list 3840.5338 870.9858) 
(list 3840.5338 870.9961) 
(list 3840.5338 871.0064) 
(list 3840.5338 871.0167) 
(list 3840.5338 871.0269) 
(list 3840.5338 871.0372) 
(list 3840.5338 871.0475) 
(list 3840.5338 871.0578) 
(list 3840.5338 871.0681) 
(list 3840.5338 871.0783) 
(list 3840.5338 871.0886) 
(list 3840.5338 871.0989) 
(list 3840.5338 871.1092) 
(list 3840.5338 871.1194) 
(list 3840.5338 871.1297) 
(list 3840.5338 871.14) 
(list 3841.132 871.14)))
(apply 'command (append '("pline") coords '("c")))
(setq tap12 (ssadd (entlast) tap12))
(command "_mirror" (entlast) "" "3840,900" "3840,901" "No")
(setq tap12 (ssadd (entlast) tap12))
(setq coords (list 
(list 3840 871.14) 
(list 3840.125 871.14) 
(list 3840.125 871.1503) 
(list 3840.125 871.1606) 
(list 3840.125 871.1708) 
(list 3840.125 871.1811) 
(list 3840.125 871.1914) 
(list 3840.125 871.2017) 
(list 3840.125 871.2119) 
(list 3840.125 871.2222) 
(list 3840.125 871.2325) 
(list 3840.125 871.2428) 
(list 3840.125 871.2531) 
(list 3840.125 871.2633) 
(list 3840.125 871.2736) 
(list 3840.125 871.2839) 
(list 3840.125 871.2942) 
(list 3840.125 871.3044) 
(list 3840.125 871.3147) 
(list 3840.125 871.325) 
(list 3840.125 871.3353) 
(list 3840.125 871.3456) 
(list 3840.125 871.3558) 
(list 3840.125 871.3661) 
(list 3840.125 871.3764) 
(list 3840.125 871.3867) 
(list 3840.125 871.3969) 
(list 3840.125 871.4072) 
(list 3840.125 871.4175) 
(list 3840.125 871.4278) 
(list 3840.125 871.4381) 
(list 3840.125 871.4483) 
(list 3840.125 871.4586) 
(list 3840.125 871.4689) 
(list 3840.125 871.4792) 
(list 3840.125 871.4894) 
(list 3840.125 871.4997) 
(list 3840.125 871.51) 
(list 3840 871.51)))
(apply 'command (append '("pline") coords '("c")))
(setq tap12 (ssadd (entlast) tap12))
(command "_mirror" (entlast) "" "3840,900" "3840,901" "No")
(setq tap12 (ssadd (entlast) tap12))
(setq coords (list 
(list 3840.5445 871.14) 
(list 3840.5338 871.14) 
(list 3840.5324 871.1503) 
(list 3840.5275 871.1606) 
(list 3840.5194 871.1708) 
(list 3840.5082 871.1811) 
(list 3840.4942 871.1914) 
(list 3840.478 871.2017) 
(list 3840.4599 871.2119) 
(list 3840.4406 871.2222) 
(list 3840.4205 871.2325) 
(list 3840.4004 871.2428) 
(list 3840.3807 871.2531) 
(list 3840.3622 871.2633) 
(list 3840.3454 871.2736) 
(list 3840.3308 871.2839) 
(list 3840.3189 871.2942) 
(list 3840.3101 871.3044) 
(list 3840.3045 871.3147) 
(list 3840.3025 871.325) 
(list 3840.3041 871.3353) 
(list 3840.3092 871.3456) 
(list 3840.3178 871.3558) 
(list 3840.3295 871.3661) 
(list 3840.3441 871.3764) 
(list 3840.3611 871.3867) 
(list 3840.38 871.3969) 
(list 3840.4002 871.4072) 
(list 3840.4212 871.4175) 
(list 3840.4422 871.4278) 
(list 3840.4627 871.4381) 
(list 3840.482 871.4483) 
(list 3840.4996 871.4586) 
(list 3840.5148 871.4689) 
(list 3840.5273 871.4792) 
(list 3840.5365 871.4894) 
(list 3840.5424 871.4997) 
(list 3840.5445 871.51) 
(list 3840.5445 871.51)))
(apply 'command (append '("pline") coords '("c")))
(setq tap12 (ssadd (entlast) tap12))
(command "_mirror" (entlast) "" "3840,900" "3840,901" "No")
(setq tap12 (ssadd (entlast) tap12))
(setq coords (list 
(list 3841.132 871.14) 
(list 3840.5445 871.14) 
(list 3840.5445 871.1503) 
(list 3840.5445 871.1606) 
(list 3840.5445 871.1708) 
(list 3840.5445 871.1811) 
(list 3840.5445 871.1914) 
(list 3840.5445 871.2017) 
(list 3840.5445 871.2119) 
(list 3840.5445 871.2222) 
(list 3840.5445 871.2325) 
(list 3840.5445 871.2428) 
(list 3840.5445 871.2531) 
(list 3840.5445 871.2633) 
(list 3840.5445 871.2736) 
(list 3840.5445 871.2839) 
(list 3840.5445 871.2942) 
(list 3840.5445 871.3044) 
(list 3840.5445 871.3147) 
(list 3840.5445 871.325) 
(list 3840.5445 871.3353) 
(list 3840.5445 871.3456) 
(list 3840.5445 871.3558) 
(list 3840.5445 871.3661) 
(list 3840.5445 871.3764) 
(list 3840.5445 871.3867) 
(list 3840.5445 871.3969) 
(list 3840.5445 871.4072) 
(list 3840.5445 871.4175) 
(list 3840.5445 871.4278) 
(list 3840.5445 871.4381) 
(list 3840.5445 871.4483) 
(list 3840.5445 871.4586) 
(list 3840.5445 871.4689) 
(list 3840.5445 871.4792) 
(list 3840.5445 871.4894) 
(list 3840.5445 871.4997) 
(list 3840.5445 871.51) 
(list 3841.132 871.51)))
(apply 'command (append '("pline") coords '("c")))
(setq tap12 (ssadd (entlast) tap12))
(command "_mirror" (entlast) "" "3840,900" "3840,901" "No")
(setq tap12 (ssadd (entlast) tap12))
(setq coords (list 
(list 3840 871.51) 
(list 3840.125 871.51) 
(list 3840.125 871.5203) 
(list 3840.125 871.5306) 
(list 3840.125 871.5408) 
(list 3840.125 871.5511) 
(list 3840.125 871.5614) 
(list 3840.125 871.5717) 
(list 3840.125 871.5819) 
(list 3840.125 871.5922) 
(list 3840.125 871.6025) 
(list 3840.125 871.6128) 
(list 3840.125 871.6231) 
(list 3840.125 871.6333) 
(list 3840.125 871.6436) 
(list 3840.125 871.6539) 
(list 3840.125 871.6642) 
(list 3840.125 871.6744) 
(list 3840.125 871.6847) 
(list 3840.125 871.695) 
(list 3840.125 871.7053) 
(list 3840.125 871.7156) 
(list 3840.125 871.7258) 
(list 3840.125 871.7361) 
(list 3840.125 871.7464) 
(list 3840.125 871.7567) 
(list 3840.125 871.7669) 
(list 3840.125 871.7772) 
(list 3840.125 871.7875) 
(list 3840.125 871.7978) 
(list 3840.125 871.8081) 
(list 3840.125 871.8183) 
(list 3840.125 871.8286) 
(list 3840.125 871.8389) 
(list 3840.125 871.8492) 
(list 3840.125 871.8594) 
(list 3840.125 871.8697) 
(list 3840.125 871.88) 
(list 3840 871.88)))
(apply 'command (append '("pline") coords '("c")))
(setq tap12 (ssadd (entlast) tap12))
(command "_mirror" (entlast) "" "3840,900" "3840,901" "No")
(setq tap12 (ssadd (entlast) tap12))
(setq coords (list 
(list 3840.5553 871.51) 
(list 3840.5445 871.51) 
(list 3840.543 871.5203) 
(list 3840.5377 871.5306) 
(list 3840.5288 871.5408) 
(list 3840.5167 871.5511) 
(list 3840.5016 871.5614) 
(list 3840.484 871.5717) 
(list 3840.4644 871.5819) 
(list 3840.4435 871.5922) 
(list 3840.4218 871.6025) 
(list 3840.4 871.6128) 
(list 3840.3788 871.6231) 
(list 3840.3588 871.6333) 
(list 3840.3406 871.6436) 
(list 3840.3249 871.6539) 
(list 3840.312 871.6642) 
(list 3840.3024 871.6744) 
(list 3840.2965 871.6847) 
(list 3840.2943 871.695) 
(list 3840.296 871.7053) 
(list 3840.3016 871.7156) 
(list 3840.3108 871.7258) 
(list 3840.3235 871.7361) 
(list 3840.3393 871.7464) 
(list 3840.3576 871.7567) 
(list 3840.378 871.7669) 
(list 3840.3998 871.7772) 
(list 3840.4224 871.7875) 
(list 3840.4451 871.7978) 
(list 3840.4672 871.8081) 
(list 3840.488 871.8183) 
(list 3840.5069 871.8286) 
(list 3840.5233 871.8389) 
(list 3840.5367 871.8492) 
(list 3840.5467 871.8594) 
(list 3840.553 871.8697) 
(list 3840.5553 871.88) 
(list 3840.5553 871.88)))
(apply 'command (append '("pline") coords '("c")))
(setq tap12 (ssadd (entlast) tap12))
(command "_mirror" (entlast) "" "3840,900" "3840,901" "No")
(setq tap12 (ssadd (entlast) tap12))
(setq coords (list 
(list 3841.132 871.51) 
(list 3840.5553 871.51) 
(list 3840.5553 871.5203) 
(list 3840.5553 871.5306) 
(list 3840.5553 871.5408) 
(list 3840.5553 871.5511) 
(list 3840.5553 871.5614) 
(list 3840.5553 871.5717) 
(list 3840.5553 871.5819) 
(list 3840.5553 871.5922) 
(list 3840.5553 871.6025) 
(list 3840.5553 871.6128) 
(list 3840.5553 871.6231) 
(list 3840.5553 871.6333) 
(list 3840.5553 871.6436) 
(list 3840.5553 871.6539) 
(list 3840.5553 871.6642) 
(list 3840.5553 871.6744) 
(list 3840.5553 871.6847) 
(list 3840.5553 871.695) 
(list 3840.5553 871.7053) 
(list 3840.5553 871.7156) 
(list 3840.5553 871.7258) 
(list 3840.5553 871.7361) 
(list 3840.5553 871.7464) 
(list 3840.5553 871.7567) 
(list 3840.5553 871.7669) 
(list 3840.5553 871.7772) 
(list 3840.5553 871.7875) 
(list 3840.5553 871.7978) 
(list 3840.5553 871.8081) 
(list 3840.5553 871.8183) 
(list 3840.5553 871.8286) 
(list 3840.5553 871.8389) 
(list 3840.5553 871.8492) 
(list 3840.5553 871.8594) 
(list 3840.5553 871.8697) 
(list 3840.5553 871.88) 
(list 3841.132 871.88)))
(apply 'command (append '("pline") coords '("c")))
(setq tap12 (ssadd (entlast) tap12))
(command "_mirror" (entlast) "" "3840,900" "3840,901" "No")
(setq tap12 (ssadd (entlast) tap12))
(setq coords (list 
(list 3840 871.88) 
(list 3840.125 871.88) 
(list 3840.125 871.8903) 
(list 3840.125 871.9006) 
(list 3840.125 871.9108) 
(list 3840.125 871.9211) 
(list 3840.125 871.9314) 
(list 3840.125 871.9417) 
(list 3840.125 871.9519) 
(list 3840.125 871.9622) 
(list 3840.125 871.9725) 
(list 3840.125 871.9828) 
(list 3840.125 871.9931) 
(list 3840.125 872.0033) 
(list 3840.125 872.0136) 
(list 3840.125 872.0239) 
(list 3840.125 872.0342) 
(list 3840.125 872.0444) 
(list 3840.125 872.0547) 
(list 3840.125 872.065) 
(list 3840.125 872.0753) 
(list 3840.125 872.0856) 
(list 3840.125 872.0958) 
(list 3840.125 872.1061) 
(list 3840.125 872.1164) 
(list 3840.125 872.1267) 
(list 3840.125 872.1369) 
(list 3840.125 872.1472) 
(list 3840.125 872.1575) 
(list 3840.125 872.1678) 
(list 3840.125 872.1781) 
(list 3840.125 872.1883) 
(list 3840.125 872.1986) 
(list 3840.125 872.2089) 
(list 3840.125 872.2192) 
(list 3840.125 872.2294) 
(list 3840.125 872.2397) 
(list 3840.125 872.25) 
(list 3840 872.25)))
(apply 'command (append '("pline") coords '("c")))
(setq tap12 (ssadd (entlast) tap12))
(command "_mirror" (entlast) "" "3840,900" "3840,901" "No")
(setq tap12 (ssadd (entlast) tap12))
(setq coords (list 
(list 3840.566 871.88) 
(list 3840.5553 871.88) 
(list 3840.5535 871.8903) 
(list 3840.5478 871.9006) 
(list 3840.5383 871.9108) 
(list 3840.5252 871.9211) 
(list 3840.5089 871.9314) 
(list 3840.49 871.9417) 
(list 3840.4689 871.9519) 
(list 3840.4464 871.9622) 
(list 3840.423 871.9725) 
(list 3840.3996 871.9828) 
(list 3840.3768 871.9931) 
(list 3840.3553 872.0033) 
(list 3840.3358 872.0136) 
(list 3840.3189 872.0239) 
(list 3840.3051 872.0342) 
(list 3840.2948 872.0444) 
(list 3840.2884 872.0547) 
(list 3840.2861 872.065) 
(list 3840.288 872.0753) 
(list 3840.294 872.0856) 
(list 3840.3039 872.0958) 
(list 3840.3175 872.1061) 
(list 3840.3345 872.1164) 
(list 3840.3542 872.1267) 
(list 3840.376 872.1369) 
(list 3840.3994 872.1472) 
(list 3840.4237 872.1575) 
(list 3840.448 872.1678) 
(list 3840.4717 872.1781) 
(list 3840.494 872.1883) 
(list 3840.5143 872.1986) 
(list 3840.5318 872.2089) 
(list 3840.5462 872.2192) 
(list 3840.5569 872.2294) 
(list 3840.5635 872.2397) 
(list 3840.566 872.25) 
(list 3840.566 872.25)))
(apply 'command (append '("pline") coords '("c")))
(setq tap12 (ssadd (entlast) tap12))
(command "_mirror" (entlast) "" "3840,900" "3840,901" "No")
(setq tap12 (ssadd (entlast) tap12))
(setq coords (list 
(list 3841.132 871.88) 
(list 3840.566 871.88) 
(list 3840.566 871.8903) 
(list 3840.566 871.9006) 
(list 3840.566 871.9108) 
(list 3840.566 871.9211) 
(list 3840.566 871.9314) 
(list 3840.566 871.9417) 
(list 3840.566 871.9519) 
(list 3840.566 871.9622) 
(list 3840.566 871.9725) 
(list 3840.566 871.9828) 
(list 3840.566 871.9931) 
(list 3840.566 872.0033) 
(list 3840.566 872.0136) 
(list 3840.566 872.0239) 
(list 3840.566 872.0342) 
(list 3840.566 872.0444) 
(list 3840.566 872.0547) 
(list 3840.566 872.065) 
(list 3840.566 872.0753) 
(list 3840.566 872.0856) 
(list 3840.566 872.0958) 
(list 3840.566 872.1061) 
(list 3840.566 872.1164) 
(list 3840.566 872.1267) 
(list 3840.566 872.1369) 
(list 3840.566 872.1472) 
(list 3840.566 872.1575) 
(list 3840.566 872.1678) 
(list 3840.566 872.1781) 
(list 3840.566 872.1883) 
(list 3840.566 872.1986) 
(list 3840.566 872.2089) 
(list 3840.566 872.2192) 
(list 3840.566 872.2294) 
(list 3840.566 872.2397) 
(list 3840.566 872.25) 
(list 3841.132 872.25)))
(apply 'command (append '("pline") coords '("c")))
(setq tap12 (ssadd (entlast) tap12))
(command "_mirror" (entlast) "" "3840,900" "3840,901" "No")
(setq tap12 (ssadd (entlast) tap12))
(command "_block" "blktap12" "3840,900" tap12 "")
(command "_insert" "blktap12" "3840,900" "1" "1" "0")
(command "_insert" "blktap12" "3840,900" "1" "1" "180")
(setq uc12 nil)
(setq uc12 (ssadd))
(setq coords (list 
(list 0 -0.185) 
(list 0.125 -0.185) 
(list 0.125 -0.17472) 
(list 0.125 -0.16444) 
(list 0.125 -0.15417) 
(list 0.125 -0.14389) 
(list 0.125 -0.13361) 
(list 0.125 -0.12333) 
(list 0.125 -0.11306) 
(list 0.125 -0.10278) 
(list 0.125 -0.0925) 
(list 0.125 -0.082222) 
(list 0.125 -0.071944) 
(list 0.125 -0.061667) 
(list 0.125 -0.051389) 
(list 0.125 -0.041111) 
(list 0.125 -0.030833) 
(list 0.125 -0.020556) 
(list 0.125 -0.010278) 
(list 0.125 0) 
(list 0.125 0.010278) 
(list 0.125 0.020556) 
(list 0.125 0.030833) 
(list 0.125 0.041111) 
(list 0.125 0.051389) 
(list 0.125 0.061667) 
(list 0.125 0.071944) 
(list 0.125 0.082222) 
(list 0.125 0.0925) 
(list 0.125 0.10278) 
(list 0.125 0.11306) 
(list 0.125 0.12333) 
(list 0.125 0.13361) 
(list 0.125 0.14389) 
(list 0.125 0.15417) 
(list 0.125 0.16444) 
(list 0.125 0.17472) 
(list 0.125 0.185) 
(list 0 0.185)))
(apply 'command (append '("pline") coords '("c")))
(setq uc12 (ssadd (entlast) uc12))
(setq coords (list 
(list 1.132 -0.185) 
(list 0.566 -0.185) 
(list 0.56384 -0.17472) 
(list 0.55744 -0.16444) 
(list 0.54698 -0.15417) 
(list 0.53278 -0.14389) 
(list 0.51528 -0.13361) 
(list 0.495 -0.12333) 
(list 0.47257 -0.11306) 
(list 0.44866 -0.10278) 
(list 0.424 -0.0925) 
(list 0.39934 -0.082222) 
(list 0.37543 -0.071944) 
(list 0.353 -0.061667) 
(list 0.33272 -0.051389) 
(list 0.31522 -0.041111) 
(list 0.30102 -0.030833) 
(list 0.29056 -0.020556) 
(list 0.28416 -0.010278) 
(list 0.282 0) 
(list 0.28416 0.010278) 
(list 0.29056 0.020556) 
(list 0.30102 0.030833) 
(list 0.31522 0.041111) 
(list 0.33272 0.051389) 
(list 0.353 0.061667) 
(list 0.37543 0.071944) 
(list 0.39934 0.082222) 
(list 0.424 0.0925) 
(list 0.44866 0.10278) 
(list 0.47257 0.11306) 
(list 0.495 0.12333) 
(list 0.51528 0.13361) 
(list 0.53278 0.14389) 
(list 0.54698 0.15417) 
(list 0.55744 0.16444) 
(list 0.56384 0.17472) 
(list 0.566 0.185) 
(list 1.132 0.185)))
(apply 'command (append '("pline") coords '("c")))
(setq uc12 (ssadd (entlast) uc12))
(command "_block" "blkuc12" "0,0.185" uc12 "")
(command "_insert" "blkuc12" "3840,872.62" "1" "1" "0")
(command "_insert" "blkuc12" "3840,872.25" "1" "1" "180")
(command "_insert" "blkuc12" "3840,872.99" "1" "1" "0")
(command "_insert" "blkuc12" "3840,872.62" "1" "1" "180")
(command "_insert" "blkuc12" "3840,873.36" "1" "1" "0")
(command "_insert" "blkuc12" "3840,872.99" "1" "1" "180")
(command "_insert" "blkuc12" "3840,873.73" "1" "1" "0")
(command "_insert" "blkuc12" "3840,873.36" "1" "1" "180")
(command "_insert" "blkuc12" "3840,874.1" "1" "1" "0")
(command "_insert" "blkuc12" "3840,873.73" "1" "1" "180")
(command "_insert" "blkuc12" "3840,874.47" "1" "1" "0")
(command "_insert" "blkuc12" "3840,874.1" "1" "1" "180")
(command "_insert" "blkuc12" "3840,874.84" "1" "1" "0")
(command "_insert" "blkuc12" "3840,874.47" "1" "1" "180")
(command "_insert" "blkuc12" "3840,875.21" "1" "1" "0")
(command "_insert" "blkuc12" "3840,874.84" "1" "1" "180")
(command "_insert" "blkuc12" "3840,875.58" "1" "1" "0")
(command "_insert" "blkuc12" "3840,875.21" "1" "1" "180")
(command "_insert" "blkuc12" "3840,875.95" "1" "1" "0")
(command "_insert" "blkuc12" "3840,875.58" "1" "1" "180")
(command "_insert" "blkuc12" "3840,876.32" "1" "1" "0")
(command "_insert" "blkuc12" "3840,875.95" "1" "1" "180")
(command "_insert" "blkuc12" "3840,876.69" "1" "1" "0")
(command "_insert" "blkuc12" "3840,876.32" "1" "1" "180")
(command "_insert" "blkuc12" "3840,877.06" "1" "1" "0")
(command "_insert" "blkuc12" "3840,876.69" "1" "1" "180")
(command "_insert" "blkuc12" "3840,877.43" "1" "1" "0")
(command "_insert" "blkuc12" "3840,877.06" "1" "1" "180")
(command "_insert" "blkuc12" "3840,877.8" "1" "1" "0")
(command "_insert" "blkuc12" "3840,877.43" "1" "1" "180")
(command "_insert" "blkuc12" "3840,878.17" "1" "1" "0")
(command "_insert" "blkuc12" "3840,877.8" "1" "1" "180")
(command "_insert" "blkuc12" "3840,878.54" "1" "1" "0")
(command "_insert" "blkuc12" "3840,878.17" "1" "1" "180")
(command "_insert" "blkuc12" "3840,878.91" "1" "1" "0")
(command "_insert" "blkuc12" "3840,878.54" "1" "1" "180")
(command "_insert" "blkuc12" "3840,879.28" "1" "1" "0")
(command "_insert" "blkuc12" "3840,878.91" "1" "1" "180")
(command "_insert" "blkuc12" "3840,879.65" "1" "1" "0")
(command "_insert" "blkuc12" "3840,879.28" "1" "1" "180")
(command "_insert" "blkuc12" "3840,880.02" "1" "1" "0")
(command "_insert" "blkuc12" "3840,879.65" "1" "1" "180")
(command "_insert" "blkuc12" "3840,880.39" "1" "1" "0")
(command "_insert" "blkuc12" "3840,880.02" "1" "1" "180")
(command "_insert" "blkuc12" "3840,880.76" "1" "1" "0")
(command "_insert" "blkuc12" "3840,880.39" "1" "1" "180")
(command "_insert" "blkuc12" "3840,881.13" "1" "1" "0")
(command "_insert" "blkuc12" "3840,880.76" "1" "1" "180")
(command "_insert" "blkuc12" "3840,881.5" "1" "1" "0")
(command "_insert" "blkuc12" "3840,881.13" "1" "1" "180")
(command "_insert" "blkuc12" "3840,881.87" "1" "1" "0")
(command "_insert" "blkuc12" "3840,881.5" "1" "1" "180")
(command "_insert" "blkuc12" "3840,882.24" "1" "1" "0")
(command "_insert" "blkuc12" "3840,881.87" "1" "1" "180")
(command "_insert" "blkuc12" "3840,882.61" "1" "1" "0")
(command "_insert" "blkuc12" "3840,882.24" "1" "1" "180")
(command "_insert" "blkuc12" "3840,882.98" "1" "1" "0")
(command "_insert" "blkuc12" "3840,882.61" "1" "1" "180")
(command "_insert" "blkuc12" "3840,883.35" "1" "1" "0")
(command "_insert" "blkuc12" "3840,882.98" "1" "1" "180")
(command "_insert" "blkuc12" "3840,883.72" "1" "1" "0")
(command "_insert" "blkuc12" "3840,883.35" "1" "1" "180")
(command "_insert" "blkuc12" "3840,884.09" "1" "1" "0")
(command "_insert" "blkuc12" "3840,883.72" "1" "1" "180")
(command "_insert" "blkuc12" "3840,884.46" "1" "1" "0")
(command "_insert" "blkuc12" "3840,884.09" "1" "1" "180")
(command "_insert" "blkuc12" "3840,884.83" "1" "1" "0")
(command "_insert" "blkuc12" "3840,884.46" "1" "1" "180")
(command "_insert" "blkuc12" "3840,885.2" "1" "1" "0")
(command "_insert" "blkuc12" "3840,884.83" "1" "1" "180")
(command "_insert" "blkuc12" "3840,885.57" "1" "1" "0")
(command "_insert" "blkuc12" "3840,885.2" "1" "1" "180")
(command "_insert" "blkuc12" "3840,885.94" "1" "1" "0")
(command "_insert" "blkuc12" "3840,885.57" "1" "1" "180")
(command "_insert" "blkuc12" "3840,886.31" "1" "1" "0")
(command "_insert" "blkuc12" "3840,885.94" "1" "1" "180")
(command "_insert" "blkuc12" "3840,886.68" "1" "1" "0")
(command "_insert" "blkuc12" "3840,886.31" "1" "1" "180")
(command "_insert" "blkuc12" "3840,887.05" "1" "1" "0")
(command "_insert" "blkuc12" "3840,886.68" "1" "1" "180")
(command "_insert" "blkuc12" "3840,887.42" "1" "1" "0")
(command "_insert" "blkuc12" "3840,887.05" "1" "1" "180")
(command "_insert" "blkuc12" "3840,887.79" "1" "1" "0")
(command "_insert" "blkuc12" "3840,887.42" "1" "1" "180")
(command "_insert" "blkuc12" "3840,888.16" "1" "1" "0")
(command "_insert" "blkuc12" "3840,887.79" "1" "1" "180")
(command "_insert" "blkuc12" "3840,888.53" "1" "1" "0")
(command "_insert" "blkuc12" "3840,888.16" "1" "1" "180")
(command "_insert" "blkuc12" "3840,888.9" "1" "1" "0")
(command "_insert" "blkuc12" "3840,888.53" "1" "1" "180")
(command "_insert" "blkuc12" "3840,889.27" "1" "1" "0")
(command "_insert" "blkuc12" "3840,888.9" "1" "1" "180")
(command "_insert" "blkuc12" "3840,889.64" "1" "1" "0")
(command "_insert" "blkuc12" "3840,889.27" "1" "1" "180")
(command "_insert" "blkuc12" "3840,890.01" "1" "1" "0")
(command "_insert" "blkuc12" "3840,889.64" "1" "1" "180")
(command "_insert" "blkuc12" "3840,890.38" "1" "1" "0")
(command "_insert" "blkuc12" "3840,890.01" "1" "1" "180")
(command "_insert" "blkuc12" "3840,890.75" "1" "1" "0")
(command "_insert" "blkuc12" "3840,890.38" "1" "1" "180")
(command "_insert" "blkuc12" "3840,891.12" "1" "1" "0")
(command "_insert" "blkuc12" "3840,890.75" "1" "1" "180")
(command "_insert" "blkuc12" "3840,891.49" "1" "1" "0")
(command "_insert" "blkuc12" "3840,891.12" "1" "1" "180")
(command "_insert" "blkuc12" "3840,891.86" "1" "1" "0")
(command "_insert" "blkuc12" "3840,891.49" "1" "1" "180")
(command "_insert" "blkuc12" "3840,892.23" "1" "1" "0")
(command "_insert" "blkuc12" "3840,891.86" "1" "1" "180")
(command "_insert" "blkuc12" "3840,892.6" "1" "1" "0")
(command "_insert" "blkuc12" "3840,892.23" "1" "1" "180")
(command "_insert" "blkuc12" "3840,892.97" "1" "1" "0")
(command "_insert" "blkuc12" "3840,892.6" "1" "1" "180")
(command "_insert" "blkuc12" "3840,893.34" "1" "1" "0")
(command "_insert" "blkuc12" "3840,892.97" "1" "1" "180")
(command "_insert" "blkuc12" "3840,893.71" "1" "1" "0")
(command "_insert" "blkuc12" "3840,893.34" "1" "1" "180")
(command "_insert" "blkuc12" "3840,894.08" "1" "1" "0")
(command "_insert" "blkuc12" "3840,893.71" "1" "1" "180")
(command "_insert" "blkuc12" "3840,894.45" "1" "1" "0")
(command "_insert" "blkuc12" "3840,894.08" "1" "1" "180")
(command "_insert" "blkuc12" "3840,894.82" "1" "1" "0")
(command "_insert" "blkuc12" "3840,894.45" "1" "1" "180")
(command "_insert" "blkuc12" "3840,895.19" "1" "1" "0")
(command "_insert" "blkuc12" "3840,894.82" "1" "1" "180")
(command "_insert" "blkuc12" "3840,895.56" "1" "1" "0")
(command "_insert" "blkuc12" "3840,895.19" "1" "1" "180")
(command "_insert" "blkuc12" "3840,895.93" "1" "1" "0")
(command "_insert" "blkuc12" "3840,895.56" "1" "1" "180")
(command "_insert" "blkuc12" "3840,896.3" "1" "1" "0")
(command "_insert" "blkuc12" "3840,895.93" "1" "1" "180")
(command "_insert" "blkuc12" "3840,896.67" "1" "1" "0")
(command "_insert" "blkuc12" "3840,896.3" "1" "1" "180")
(command "_insert" "blkuc12" "3840,897.04" "1" "1" "0")
(command "_insert" "blkuc12" "3840,896.67" "1" "1" "180")
(command "_insert" "blkuc12" "3840,897.41" "1" "1" "0")
(command "_insert" "blkuc12" "3840,897.04" "1" "1" "180")
(command "_insert" "blkuc12" "3840,897.78" "1" "1" "0")
(command "_insert" "blkuc12" "3840,897.41" "1" "1" "180")
(command "_insert" "blkuc12" "3840,898.15" "1" "1" "0")
(command "_insert" "blkuc12" "3840,897.78" "1" "1" "180")
(command "_insert" "blkuc12" "3840,898.52" "1" "1" "0")
(command "_insert" "blkuc12" "3840,898.15" "1" "1" "180")
(command "_insert" "blkuc12" "3840,898.89" "1" "1" "0")
(command "_insert" "blkuc12" "3840,898.52" "1" "1" "180")
(command "_insert" "blkuc12" "3840,899.26" "1" "1" "0")
(command "_insert" "blkuc12" "3840,898.89" "1" "1" "180")
(command "_insert" "blkuc12" "3840,899.63" "1" "1" "0")
(command "_insert" "blkuc12" "3840,899.26" "1" "1" "180")
(command "_insert" "blkuc12" "3840,900" "1" "1" "0")
(command "_insert" "blkuc12" "3840,899.63" "1" "1" "180")
(command "_insert" "blkuc12" "3840,900.37" "1" "1" "0")
(command "_insert" "blkuc12" "3840,900" "1" "1" "180")
(command "_insert" "blkuc12" "3840,900.74" "1" "1" "0")
(command "_insert" "blkuc12" "3840,900.37" "1" "1" "180")
(command "_insert" "blkuc12" "3840,901.11" "1" "1" "0")
(command "_insert" "blkuc12" "3840,900.74" "1" "1" "180")
(command "_insert" "blkuc12" "3840,901.48" "1" "1" "0")
(command "_insert" "blkuc12" "3840,901.11" "1" "1" "180")
(command "_insert" "blkuc12" "3840,901.85" "1" "1" "0")
(command "_insert" "blkuc12" "3840,901.48" "1" "1" "180")
(command "_insert" "blkuc12" "3840,902.22" "1" "1" "0")
(command "_insert" "blkuc12" "3840,901.85" "1" "1" "180")
(command "_insert" "blkuc12" "3840,902.59" "1" "1" "0")
(command "_insert" "blkuc12" "3840,902.22" "1" "1" "180")
(command "_insert" "blkuc12" "3840,902.96" "1" "1" "0")
(command "_insert" "blkuc12" "3840,902.59" "1" "1" "180")
(command "_insert" "blkuc12" "3840,903.33" "1" "1" "0")
(command "_insert" "blkuc12" "3840,902.96" "1" "1" "180")
(command "_insert" "blkuc12" "3840,903.7" "1" "1" "0")
(command "_insert" "blkuc12" "3840,903.33" "1" "1" "180")
(command "_insert" "blkuc12" "3840,904.07" "1" "1" "0")
(command "_insert" "blkuc12" "3840,903.7" "1" "1" "180")
(command "_insert" "blkuc12" "3840,904.44" "1" "1" "0")
(command "_insert" "blkuc12" "3840,904.07" "1" "1" "180")
(command "_insert" "blkuc12" "3840,904.81" "1" "1" "0")
(command "_insert" "blkuc12" "3840,904.44" "1" "1" "180")
(command "_insert" "blkuc12" "3840,905.18" "1" "1" "0")
(command "_insert" "blkuc12" "3840,904.81" "1" "1" "180")
(command "_insert" "blkuc12" "3840,905.55" "1" "1" "0")
(command "_insert" "blkuc12" "3840,905.18" "1" "1" "180")
(command "_insert" "blkuc12" "3840,905.92" "1" "1" "0")
(command "_insert" "blkuc12" "3840,905.55" "1" "1" "180")
(command "_insert" "blkuc12" "3840,906.29" "1" "1" "0")
(command "_insert" "blkuc12" "3840,905.92" "1" "1" "180")
(command "_insert" "blkuc12" "3840,906.66" "1" "1" "0")
(command "_insert" "blkuc12" "3840,906.29" "1" "1" "180")
(command "_insert" "blkuc12" "3840,907.03" "1" "1" "0")
(command "_insert" "blkuc12" "3840,906.66" "1" "1" "180")
(command "_insert" "blkuc12" "3840,907.4" "1" "1" "0")
(command "_insert" "blkuc12" "3840,907.03" "1" "1" "180")
(command "_insert" "blkuc12" "3840,907.77" "1" "1" "0")
(command "_insert" "blkuc12" "3840,907.4" "1" "1" "180")
(command "_insert" "blkuc12" "3840,908.14" "1" "1" "0")
(command "_insert" "blkuc12" "3840,907.77" "1" "1" "180")
(command "_insert" "blkuc12" "3840,908.51" "1" "1" "0")
(command "_insert" "blkuc12" "3840,908.14" "1" "1" "180")
(command "_insert" "blkuc12" "3840,908.88" "1" "1" "0")
(command "_insert" "blkuc12" "3840,908.51" "1" "1" "180")
(command "_insert" "blkuc12" "3840,909.25" "1" "1" "0")
(command "_insert" "blkuc12" "3840,908.88" "1" "1" "180")
(command "_insert" "blkuc12" "3840,909.62" "1" "1" "0")
(command "_insert" "blkuc12" "3840,909.25" "1" "1" "180")
(command "_insert" "blkuc12" "3840,909.99" "1" "1" "0")
(command "_insert" "blkuc12" "3840,909.62" "1" "1" "180")
(command "_insert" "blkuc12" "3840,910.36" "1" "1" "0")
(command "_insert" "blkuc12" "3840,909.99" "1" "1" "180")
(command "_insert" "blkuc12" "3840,910.73" "1" "1" "0")
(command "_insert" "blkuc12" "3840,910.36" "1" "1" "180")
(command "_insert" "blkuc12" "3840,911.1" "1" "1" "0")
(command "_insert" "blkuc12" "3840,910.73" "1" "1" "180")
(command "_insert" "blkuc12" "3840,911.47" "1" "1" "0")
(command "_insert" "blkuc12" "3840,911.1" "1" "1" "180")
(command "_insert" "blkuc12" "3840,911.84" "1" "1" "0")
(command "_insert" "blkuc12" "3840,911.47" "1" "1" "180")
(command "_insert" "blkuc12" "3840,912.21" "1" "1" "0")
(command "_insert" "blkuc12" "3840,911.84" "1" "1" "180")
(command "_insert" "blkuc12" "3840,912.58" "1" "1" "0")
(command "_insert" "blkuc12" "3840,912.21" "1" "1" "180")
(command "_insert" "blkuc12" "3840,912.95" "1" "1" "0")
(command "_insert" "blkuc12" "3840,912.58" "1" "1" "180")
(command "_insert" "blkuc12" "3840,913.32" "1" "1" "0")
(command "_insert" "blkuc12" "3840,912.95" "1" "1" "180")
(command "_insert" "blkuc12" "3840,913.69" "1" "1" "0")
(command "_insert" "blkuc12" "3840,913.32" "1" "1" "180")
(command "_insert" "blkuc12" "3840,914.06" "1" "1" "0")
(command "_insert" "blkuc12" "3840,913.69" "1" "1" "180")
(command "_insert" "blkuc12" "3840,914.43" "1" "1" "0")
(command "_insert" "blkuc12" "3840,914.06" "1" "1" "180")
(command "_insert" "blkuc12" "3840,914.8" "1" "1" "0")
(command "_insert" "blkuc12" "3840,914.43" "1" "1" "180")
(command "_insert" "blkuc12" "3840,915.17" "1" "1" "0")
(command "_insert" "blkuc12" "3840,914.8" "1" "1" "180")
(command "_insert" "blkuc12" "3840,915.54" "1" "1" "0")
(command "_insert" "blkuc12" "3840,915.17" "1" "1" "180")
(command "_insert" "blkuc12" "3840,915.91" "1" "1" "0")
(command "_insert" "blkuc12" "3840,915.54" "1" "1" "180")
(command "_insert" "blkuc12" "3840,916.28" "1" "1" "0")
(command "_insert" "blkuc12" "3840,915.91" "1" "1" "180")
(command "_insert" "blkuc12" "3840,916.65" "1" "1" "0")
(command "_insert" "blkuc12" "3840,916.28" "1" "1" "180")
(command "_insert" "blkuc12" "3840,917.02" "1" "1" "0")
(command "_insert" "blkuc12" "3840,916.65" "1" "1" "180")
(command "_insert" "blkuc12" "3840,917.39" "1" "1" "0")
(command "_insert" "blkuc12" "3840,917.02" "1" "1" "180")
(command "_insert" "blkuc12" "3840,917.76" "1" "1" "0")
(command "_insert" "blkuc12" "3840,917.39" "1" "1" "180")
(command "_insert" "blkuc12" "3840,918.13" "1" "1" "0")
(command "_insert" "blkuc12" "3840,917.76" "1" "1" "180")
(command "_insert" "blkuc12" "3840,918.5" "1" "1" "0")
(command "_insert" "blkuc12" "3840,918.13" "1" "1" "180")
(command "_insert" "blkuc12" "3840,918.87" "1" "1" "0")
(command "_insert" "blkuc12" "3840,918.5" "1" "1" "180")
(command "_insert" "blkuc12" "3840,919.24" "1" "1" "0")
(command "_insert" "blkuc12" "3840,918.87" "1" "1" "180")
(command "_insert" "blkuc12" "3840,919.61" "1" "1" "0")
(command "_insert" "blkuc12" "3840,919.24" "1" "1" "180")
(command "_insert" "blkuc12" "3840,919.98" "1" "1" "0")
(command "_insert" "blkuc12" "3840,919.61" "1" "1" "180")
(command "_insert" "blkuc12" "3840,920.35" "1" "1" "0")
(command "_insert" "blkuc12" "3840,919.98" "1" "1" "180")
(command "_insert" "blkuc12" "3840,920.72" "1" "1" "0")
(command "_insert" "blkuc12" "3840,920.35" "1" "1" "180")
(command "_insert" "blkuc12" "3840,921.09" "1" "1" "0")
(command "_insert" "blkuc12" "3840,920.72" "1" "1" "180")
(command "_insert" "blkuc12" "3840,921.46" "1" "1" "0")
(command "_insert" "blkuc12" "3840,921.09" "1" "1" "180")
(command "_insert" "blkuc12" "3840,921.83" "1" "1" "0")
(command "_insert" "blkuc12" "3840,921.46" "1" "1" "180")
(command "_insert" "blkuc12" "3840,922.2" "1" "1" "0")
(command "_insert" "blkuc12" "3840,921.83" "1" "1" "180")
(command "_insert" "blkuc12" "3840,922.57" "1" "1" "0")
(command "_insert" "blkuc12" "3840,922.2" "1" "1" "180")
(command "_insert" "blkuc12" "3840,922.94" "1" "1" "0")
(command "_insert" "blkuc12" "3840,922.57" "1" "1" "180")
(command "_insert" "blkuc12" "3840,923.31" "1" "1" "0")
(command "_insert" "blkuc12" "3840,922.94" "1" "1" "180")
(command "_insert" "blkuc12" "3840,923.68" "1" "1" "0")
(command "_insert" "blkuc12" "3840,923.31" "1" "1" "180")
(command "_insert" "blkuc12" "3840,924.05" "1" "1" "0")
(command "_insert" "blkuc12" "3840,923.68" "1" "1" "180")
(command "_insert" "blkuc12" "3840,924.42" "1" "1" "0")
(command "_insert" "blkuc12" "3840,924.05" "1" "1" "180")
(command "_insert" "blkuc12" "3840,924.79" "1" "1" "0")
(command "_insert" "blkuc12" "3840,924.42" "1" "1" "180")
(command "_insert" "blkuc12" "3840,925.16" "1" "1" "0")
(command "_insert" "blkuc12" "3840,924.79" "1" "1" "180")
(command "_insert" "blkuc12" "3840,925.53" "1" "1" "0")
(command "_insert" "blkuc12" "3840,925.16" "1" "1" "180")
(command "_insert" "blkuc12" "3840,925.9" "1" "1" "0")
(command "_insert" "blkuc12" "3840,925.53" "1" "1" "180")
(command "_insert" "blkuc12" "3840,926.27" "1" "1" "0")
(command "_insert" "blkuc12" "3840,925.9" "1" "1" "180")
(command "_insert" "blkuc12" "3840,926.64" "1" "1" "0")
(command "_insert" "blkuc12" "3840,926.27" "1" "1" "180")
(command "_insert" "blkuc12" "3840,927.01" "1" "1" "0")
(command "_insert" "blkuc12" "3840,926.64" "1" "1" "180")
(command "_insert" "blkuc12" "3840,927.38" "1" "1" "0")
(command "_insert" "blkuc12" "3840,927.01" "1" "1" "180")
(command "_insert" "blkuc12" "3840,927.75" "1" "1" "0")
(command "_insert" "blkuc12" "3840,927.38" "1" "1" "180")
(command "_layer" "set" "phccover" "")
(command "_rectangle" "3838.868,933.3" "3841.132,866.7")
(command "_layer" "set" "nitride" "")
(setq phc12 currobj)
(command "_layer" "set" "cover" "")
(command "_rectangle" "3838.868,836.7" "3841.132,963.3")
(command "_layer" "set" "nitride" "")
(command "_layer" "set" "text" "")
(command "_circle" "3837.918,846.7" "0.075")
(command "_circle" "3837.543,846.7" "0.15")
(command "_circle" "3837.168,846.7" "0.075")
(command "_circle" "3836.793,846.7" "0.15")
(command "_circle" "3837.918,848.7" "0.075")
(command "_circle" "3837.543,848.7" "0.075")
(command "_circle" "3837.168,848.7" "0.15")
(command "_circle" "3836.793,848.7" "0.15")
(command "_circle" "3837.918,850.7" "0.075")
(command "_circle" "3837.543,850.7" "0.15")
(command "_circle" "3837.168,850.7" "0.15")
(command "_circle" "3836.793,850.7" "0.15")
(command "_circle" "3837.918,852.7" "0.075")
(command "_circle" "3837.543,852.7" "0.075")
(command "_circle" "3837.168,852.7" "0.075")
(command "_circle" "3836.793,852.7" "0.075")
(command "_circle" "3836.418,852.7" "0.15")
(command "_circle" "3837.918,854.7" "0.075")
(command "_circle" "3837.543,854.7" "0.15")
(command "_circle" "3837.168,854.7" "0.075")
(command "_circle" "3836.793,854.7" "0.075")
(command "_circle" "3836.418,854.7" "0.15")
(command "_circle" "3837.918,856.7" "0.075")
(command "_circle" "3837.543,856.7" "0.075")
(command "_circle" "3837.168,856.7" "0.15")
(command "_circle" "3836.793,856.7" "0.075")
(command "_circle" "3836.418,856.7" "0.15")
(command "_circle" "3837.918,858.7" "0.075")
(command "_circle" "3837.543,858.7" "0.15")
(command "_circle" "3837.168,858.7" "0.15")
(command "_circle" "3836.793,858.7" "0.075")
(command "_circle" "3836.418,858.7" "0.15")
(command "_circle" "3837.918,860.7" "0.075")
(command "_circle" "3837.543,860.7" "0.075")
(command "_circle" "3837.168,860.7" "0.075")
(command "_circle" "3836.793,860.7" "0.15")
(command "_circle" "3836.418,860.7" "0.15")
(command "_circle" "3837.918,862.7" "0.075")
(command "_circle" "3837.543,862.7" "0.15")
(command "_circle" "3837.168,862.7" "0.075")
(command "_circle" "3836.793,862.7" "0.15")
(command "_circle" "3836.418,862.7" "0.15")
(command "_circle" "3837.918,864.7" "0.075")
(command "_circle" "3837.543,864.7" "0.075")
(command "_circle" "3837.168,864.7" "0.15")
(command "_circle" "3836.793,864.7" "0.15")
(command "_circle" "3836.418,864.7" "0.15")
(command "_circle" "3837.918,866.7" "0.075")
(command "_circle" "3837.543,866.7" "0.15")
(command "_circle" "3837.168,866.7" "0.15")
(command "_circle" "3836.793,866.7" "0.15")
(command "_circle" "3836.418,866.7" "0.15")
(command "_circle" "3837.918,868.7" "0.075")
(command "_circle" "3837.543,868.7" "0.075")
(command "_circle" "3837.168,868.7" "0.075")
(command "_circle" "3836.793,868.7" "0.075")
(command "_circle" "3836.418,868.7" "0.075")
(command "_circle" "3836.043,868.7" "0.15")
(command "_circle" "3837.918,870.7" "0.075")
(command "_circle" "3837.543,870.7" "0.15")
(command "_circle" "3837.168,870.7" "0.075")
(command "_circle" "3836.793,870.7" "0.075")
(command "_circle" "3836.418,870.7" "0.075")
(command "_circle" "3836.043,870.7" "0.15")
(command "_circle" "3837.918,872.7" "0.075")
(command "_circle" "3837.543,872.7" "0.075")
(command "_circle" "3837.168,872.7" "0.15")
(command "_circle" "3836.793,872.7" "0.075")
(command "_circle" "3836.418,872.7" "0.075")
(command "_circle" "3836.043,872.7" "0.15")
(command "_circle" "3837.918,874.7" "0.075")
(command "_circle" "3837.543,874.7" "0.15")
(command "_circle" "3837.168,874.7" "0.15")
(command "_circle" "3836.793,874.7" "0.075")
(command "_circle" "3836.418,874.7" "0.075")
(command "_circle" "3836.043,874.7" "0.15")
(command "_circle" "3837.918,876.7" "0.075")
(command "_circle" "3837.543,876.7" "0.075")
(command "_circle" "3837.168,876.7" "0.075")
(command "_circle" "3836.793,876.7" "0.15")
(command "_circle" "3836.418,876.7" "0.075")
(command "_circle" "3836.043,876.7" "0.15")
(command "_circle" "3837.918,878.7" "0.075")
(command "_circle" "3837.543,878.7" "0.15")
(command "_circle" "3837.168,878.7" "0.075")
(command "_circle" "3836.793,878.7" "0.15")
(command "_circle" "3836.418,878.7" "0.075")
(command "_circle" "3836.043,878.7" "0.15")
(command "_circle" "3837.918,880.7" "0.075")
(command "_circle" "3837.543,880.7" "0.075")
(command "_circle" "3837.168,880.7" "0.15")
(command "_circle" "3836.793,880.7" "0.15")
(command "_circle" "3836.418,880.7" "0.075")
(command "_circle" "3836.043,880.7" "0.15")
(command "_circle" "3837.918,882.7" "0.075")
(command "_circle" "3837.543,882.7" "0.15")
(command "_circle" "3837.168,882.7" "0.15")
(command "_circle" "3836.793,882.7" "0.15")
(command "_circle" "3836.418,882.7" "0.075")
(command "_circle" "3836.043,882.7" "0.15")
(command "_circle" "3837.918,884.7" "0.075")
(command "_circle" "3837.543,884.7" "0.075")
(command "_circle" "3837.168,884.7" "0.075")
(command "_circle" "3836.793,884.7" "0.075")
(command "_circle" "3836.418,884.7" "0.15")
(command "_circle" "3836.043,884.7" "0.15")
(command "_circle" "3837.918,886.7" "0.075")
(command "_circle" "3837.543,886.7" "0.15")
(command "_circle" "3837.168,886.7" "0.075")
(command "_circle" "3836.793,886.7" "0.075")
(command "_circle" "3836.418,886.7" "0.15")
(command "_circle" "3836.043,886.7" "0.15")
(command "_circle" "3837.918,888.7" "0.075")
(command "_circle" "3837.543,888.7" "0.075")
(command "_circle" "3837.168,888.7" "0.15")
(command "_circle" "3836.793,888.7" "0.075")
(command "_circle" "3836.418,888.7" "0.15")
(command "_circle" "3836.043,888.7" "0.15")
(command "_circle" "3837.918,890.7" "0.075")
(command "_circle" "3837.543,890.7" "0.15")
(command "_circle" "3837.168,890.7" "0.15")
(command "_circle" "3836.793,890.7" "0.075")
(command "_circle" "3836.418,890.7" "0.15")
(command "_circle" "3836.043,890.7" "0.15")
(command "_circle" "3837.918,892.7" "0.075")
(command "_circle" "3837.543,892.7" "0.075")
(command "_circle" "3837.168,892.7" "0.075")
(command "_circle" "3836.793,892.7" "0.15")
(command "_circle" "3836.418,892.7" "0.15")
(command "_circle" "3836.043,892.7" "0.15")
(command "_circle" "3837.918,894.7" "0.075")
(command "_circle" "3837.543,894.7" "0.15")
(command "_circle" "3837.168,894.7" "0.075")
(command "_circle" "3836.793,894.7" "0.15")
(command "_circle" "3836.418,894.7" "0.15")
(command "_circle" "3836.043,894.7" "0.15")
(command "_circle" "3837.918,896.7" "0.075")
(command "_circle" "3837.543,896.7" "0.075")
(command "_circle" "3837.168,896.7" "0.15")
(command "_circle" "3836.793,896.7" "0.15")
(command "_circle" "3836.418,896.7" "0.15")
(command "_circle" "3836.043,896.7" "0.15")
(command "_circle" "3837.918,898.7" "0.075")
(command "_circle" "3837.543,898.7" "0.15")
(command "_circle" "3837.168,898.7" "0.15")
(command "_circle" "3836.793,898.7" "0.15")
(command "_circle" "3836.418,898.7" "0.15")
(command "_circle" "3836.043,898.7" "0.15")
(command "_circle" "3837.918,900.7" "0.075")
(command "_circle" "3837.543,900.7" "0.075")
(command "_circle" "3837.168,900.7" "0.075")
(command "_circle" "3836.793,900.7" "0.075")
(command "_circle" "3836.418,900.7" "0.075")
(command "_circle" "3836.043,900.7" "0.075")
(command "_circle" "3835.668,900.7" "0.15")
(command "_circle" "3837.918,902.7" "0.075")
(command "_circle" "3837.543,902.7" "0.15")
(command "_circle" "3837.168,902.7" "0.075")
(command "_circle" "3836.793,902.7" "0.075")
(command "_circle" "3836.418,902.7" "0.075")
(command "_circle" "3836.043,902.7" "0.075")
(command "_circle" "3835.668,902.7" "0.15")
(command "_circle" "3837.918,904.7" "0.075")
(command "_circle" "3837.543,904.7" "0.075")
(command "_circle" "3837.168,904.7" "0.15")
(command "_circle" "3836.793,904.7" "0.075")
(command "_circle" "3836.418,904.7" "0.075")
(command "_circle" "3836.043,904.7" "0.075")
(command "_circle" "3835.668,904.7" "0.15")
(command "_circle" "3837.918,906.7" "0.075")
(command "_circle" "3837.543,906.7" "0.15")
(command "_circle" "3837.168,906.7" "0.15")
(command "_circle" "3836.793,906.7" "0.075")
(command "_circle" "3836.418,906.7" "0.075")
(command "_circle" "3836.043,906.7" "0.075")
(command "_circle" "3835.668,906.7" "0.15")
(command "_circle" "3837.918,908.7" "0.075")
(command "_circle" "3837.543,908.7" "0.075")
(command "_circle" "3837.168,908.7" "0.075")
(command "_circle" "3836.793,908.7" "0.15")
(command "_circle" "3836.418,908.7" "0.075")
(command "_circle" "3836.043,908.7" "0.075")
(command "_circle" "3835.668,908.7" "0.15")
(command "_circle" "3837.918,910.7" "0.075")
(command "_circle" "3837.543,910.7" "0.15")
(command "_circle" "3837.168,910.7" "0.075")
(command "_circle" "3836.793,910.7" "0.15")
(command "_circle" "3836.418,910.7" "0.075")
(command "_circle" "3836.043,910.7" "0.075")
(command "_circle" "3835.668,910.7" "0.15")
(command "_circle" "3837.918,912.7" "0.075")
(command "_circle" "3837.543,912.7" "0.075")
(command "_circle" "3837.168,912.7" "0.15")
(command "_circle" "3836.793,912.7" "0.15")
(command "_circle" "3836.418,912.7" "0.075")
(command "_circle" "3836.043,912.7" "0.075")
(command "_circle" "3835.668,912.7" "0.15")
(command "_circle" "3837.918,914.7" "0.075")
(command "_circle" "3837.543,914.7" "0.15")
(command "_circle" "3837.168,914.7" "0.15")
(command "_circle" "3836.793,914.7" "0.15")
(command "_circle" "3836.418,914.7" "0.075")
(command "_circle" "3836.043,914.7" "0.075")
(command "_circle" "3835.668,914.7" "0.15")
(command "_circle" "3837.918,916.7" "0.075")
(command "_circle" "3837.543,916.7" "0.075")
(command "_circle" "3837.168,916.7" "0.075")
(command "_circle" "3836.793,916.7" "0.075")
(command "_circle" "3836.418,916.7" "0.15")
(command "_circle" "3836.043,916.7" "0.075")
(command "_circle" "3835.668,916.7" "0.15")
(command "_circle" "3837.918,918.7" "0.075")
(command "_circle" "3837.543,918.7" "0.15")
(command "_circle" "3837.168,918.7" "0.075")
(command "_circle" "3836.793,918.7" "0.075")
(command "_circle" "3836.418,918.7" "0.15")
(command "_circle" "3836.043,918.7" "0.075")
(command "_circle" "3835.668,918.7" "0.15")
(command "_circle" "3837.918,920.7" "0.075")
(command "_circle" "3837.543,920.7" "0.075")
(command "_circle" "3837.168,920.7" "0.15")
(command "_circle" "3836.793,920.7" "0.075")
(command "_circle" "3836.418,920.7" "0.15")
(command "_circle" "3836.043,920.7" "0.075")
(command "_circle" "3835.668,920.7" "0.15")
(command "_circle" "3837.918,922.7" "0.075")
(command "_circle" "3837.543,922.7" "0.15")
(command "_circle" "3837.168,922.7" "0.15")
(command "_circle" "3836.793,922.7" "0.075")
(command "_circle" "3836.418,922.7" "0.15")
(command "_circle" "3836.043,922.7" "0.075")
(command "_circle" "3835.668,922.7" "0.15")
(command "_circle" "3837.918,924.7" "0.075")
(command "_circle" "3837.543,924.7" "0.075")
(command "_circle" "3837.168,924.7" "0.075")
(command "_circle" "3836.793,924.7" "0.15")
(command "_circle" "3836.418,924.7" "0.15")
(command "_circle" "3836.043,924.7" "0.075")
(command "_circle" "3835.668,924.7" "0.15")
(command "_circle" "3837.918,926.7" "0.075")
(command "_circle" "3837.543,926.7" "0.15")
(command "_circle" "3837.168,926.7" "0.075")
(command "_circle" "3836.793,926.7" "0.15")
(command "_circle" "3836.418,926.7" "0.15")
(command "_circle" "3836.043,926.7" "0.075")
(command "_circle" "3835.668,926.7" "0.15")
(command "_circle" "3837.918,928.7" "0.075")
(command "_circle" "3837.543,928.7" "0.075")
(command "_circle" "3837.168,928.7" "0.15")
(command "_circle" "3836.793,928.7" "0.15")
(command "_circle" "3836.418,928.7" "0.15")
(command "_circle" "3836.043,928.7" "0.075")
(command "_circle" "3835.668,928.7" "0.15")
(command "_circle" "3837.918,930.7" "0.075")
(command "_circle" "3837.543,930.7" "0.15")
(command "_circle" "3837.168,930.7" "0.15")
(command "_circle" "3836.793,930.7" "0.15")
(command "_circle" "3836.418,930.7" "0.15")
(command "_circle" "3836.043,930.7" "0.075")
(command "_circle" "3835.668,930.7" "0.15")
(command "_circle" "3837.918,932.7" "0.075")
(command "_circle" "3837.543,932.7" "0.075")
(command "_circle" "3837.168,932.7" "0.075")
(command "_circle" "3836.793,932.7" "0.075")
(command "_circle" "3836.418,932.7" "0.075")
(command "_circle" "3836.043,932.7" "0.15")
(command "_circle" "3835.668,932.7" "0.15")
(command "_circle" "3837.918,934.7" "0.075")
(command "_circle" "3837.543,934.7" "0.15")
(command "_circle" "3837.168,934.7" "0.075")
(command "_circle" "3836.793,934.7" "0.075")
(command "_circle" "3836.418,934.7" "0.075")
(command "_circle" "3836.043,934.7" "0.15")
(command "_circle" "3835.668,934.7" "0.15")
(command "_circle" "3837.918,936.7" "0.075")
(command "_circle" "3837.543,936.7" "0.075")
(command "_circle" "3837.168,936.7" "0.15")
(command "_circle" "3836.793,936.7" "0.075")
(command "_circle" "3836.418,936.7" "0.075")
(command "_circle" "3836.043,936.7" "0.15")
(command "_circle" "3835.668,936.7" "0.15")
(command "_circle" "3837.918,938.7" "0.075")
(command "_circle" "3837.543,938.7" "0.15")
(command "_circle" "3837.168,938.7" "0.15")
(command "_circle" "3836.793,938.7" "0.075")
(command "_circle" "3836.418,938.7" "0.075")
(command "_circle" "3836.043,938.7" "0.15")
(command "_circle" "3835.668,938.7" "0.15")
(command "_circle" "3837.918,940.7" "0.075")
(command "_circle" "3837.543,940.7" "0.075")
(command "_circle" "3837.168,940.7" "0.075")
(command "_circle" "3836.793,940.7" "0.15")
(command "_circle" "3836.418,940.7" "0.075")
(command "_circle" "3836.043,940.7" "0.15")
(command "_circle" "3835.668,940.7" "0.15")
(command "_circle" "3837.918,942.7" "0.075")
(command "_circle" "3837.543,942.7" "0.15")
(command "_circle" "3837.168,942.7" "0.075")
(command "_circle" "3836.793,942.7" "0.15")
(command "_circle" "3836.418,942.7" "0.075")
(command "_circle" "3836.043,942.7" "0.15")
(command "_circle" "3835.668,942.7" "0.15")
(command "_circle" "3837.918,944.7" "0.075")
(command "_circle" "3837.543,944.7" "0.075")
(command "_circle" "3837.168,944.7" "0.15")
(command "_circle" "3836.793,944.7" "0.15")
(command "_circle" "3836.418,944.7" "0.075")
(command "_circle" "3836.043,944.7" "0.15")
(command "_circle" "3835.668,944.7" "0.15")
(command "_circle" "3837.918,946.7" "0.075")
(command "_circle" "3837.543,946.7" "0.15")
(command "_circle" "3837.168,946.7" "0.15")
(command "_circle" "3836.793,946.7" "0.15")
(command "_circle" "3836.418,946.7" "0.075")
(command "_circle" "3836.043,946.7" "0.15")
(command "_circle" "3835.668,946.7" "0.15")
(command "_circle" "3837.918,948.7" "0.075")
(command "_circle" "3837.543,948.7" "0.075")
(command "_circle" "3837.168,948.7" "0.075")
(command "_circle" "3836.793,948.7" "0.075")
(command "_circle" "3836.418,948.7" "0.15")
(command "_circle" "3836.043,948.7" "0.15")
(command "_circle" "3835.668,948.7" "0.15")
(command "_circle" "3837.918,950.7" "0.075")
(command "_circle" "3837.543,950.7" "0.15")
(command "_circle" "3837.168,950.7" "0.075")
(command "_circle" "3836.793,950.7" "0.075")
(command "_circle" "3836.418,950.7" "0.15")
(command "_circle" "3836.043,950.7" "0.15")
(command "_circle" "3835.668,950.7" "0.15")
(command "_circle" "3837.918,952.7" "0.075")
(command "_circle" "3837.543,952.7" "0.075")
(command "_circle" "3837.168,952.7" "0.15")
(command "_circle" "3836.793,952.7" "0.075")
(command "_circle" "3836.418,952.7" "0.15")
(command "_circle" "3836.043,952.7" "0.15")
(command "_circle" "3835.668,952.7" "0.15")
(command "_circle" "3837.918,954.7" "0.075")
(command "_circle" "3837.543,954.7" "0.15")
(command "_circle" "3837.168,954.7" "0.15")
(command "_circle" "3836.793,954.7" "0.075")
(command "_circle" "3836.418,954.7" "0.15")
(command "_circle" "3836.043,954.7" "0.15")
(command "_circle" "3835.668,954.7" "0.15")
(command "_circle" "3837.918,956.7" "0.075")
(command "_circle" "3837.543,956.7" "0.075")
(command "_circle" "3837.168,956.7" "0.075")
(command "_circle" "3836.793,956.7" "0.15")
(command "_circle" "3836.418,956.7" "0.15")
(command "_circle" "3836.043,956.7" "0.15")
(command "_circle" "3835.668,956.7" "0.15")
(command "_circle" "3837.918,958.7" "0.075")
(command "_circle" "3837.543,958.7" "0.15")
(command "_circle" "3837.168,958.7" "0.075")
(command "_circle" "3836.793,958.7" "0.15")
(command "_circle" "3836.418,958.7" "0.15")
(command "_circle" "3836.043,958.7" "0.15")
(command "_circle" "3835.668,958.7" "0.15")
(command "_circle" "3837.918,960.7" "0.075")
(command "_circle" "3837.543,960.7" "0.075")
(command "_circle" "3837.168,960.7" "0.15")
(command "_circle" "3836.793,960.7" "0.15")
(command "_circle" "3836.418,960.7" "0.15")
(command "_circle" "3836.043,960.7" "0.15")
(command "_circle" "3835.668,960.7" "0.15")
(command "_circle" "3837.918,962.7" "0.075")
(command "_circle" "3837.543,962.7" "0.15")
(command "_circle" "3837.168,962.7" "0.15")
(command "_circle" "3836.793,962.7" "0.15")
(command "_circle" "3836.418,962.7" "0.15")
(command "_circle" "3836.043,962.7" "0.15")
(command "_circle" "3835.668,962.7" "0.15")
(command "_layer" "set" "nitride" "")
(command "_layer" "set" "text" "")
(command-s "_text" "3826.868,963.3" "2" "-90" "a = 370 nm" )
(sssetfirst nil (ssget "_L"))
(if (not (numberp (vl-string-search "Mac" (getvar "platform")))) (c:txtexp))
(command "_layer" "set" "nitride" "")
(command "_layer" "set" "text" "")
(command-s "_text" "3823.868,963.3" "2" "-90" "gap = 250 nm" )
(sssetfirst nil (ssget "_L"))
(if (not (numberp (vl-string-search "Mac" (getvar "platform")))) (c:txtexp))
(command "_layer" "set" "nitride" "")
(command "_layer" "set" "text" "")
(command-s "_text" "3820.868,963.3" "2" "-90" "amplitude = 142 nm" )
(sssetfirst nil (ssget "_L"))
(if (not (numberp (vl-string-search "Mac" (getvar "platform")))) (c:txtexp))
(command "_layer" "set" "nitride" "")
(command "_layer" "set" "text" "")
(command-s "_text" "3817.868,963.3" "2" "-90" "start width = 280 nm" )
(sssetfirst nil (ssget "_L"))
(if (not (numberp (vl-string-search "Mac" (getvar "platform")))) (c:txtexp))
(command "_layer" "set" "nitride" "")
(command "_layer" "set" "text" "")
(command-s "_text" "3814.868,963.3" "2" "-90" "width = 299 nm" )
(sssetfirst nil (ssget "_L"))
(if (not (numberp (vl-string-search "Mac" (getvar "platform")))) (c:txtexp))
(command "_layer" "set" "nitride" "")
(command "_layer" "set" "text" "")
(command-s "_text" "3811.868,963.3" "2" "-90" "taper: 15" )
(sssetfirst nil (ssget "_L"))
(if (not (numberp (vl-string-search "Mac" (getvar "platform")))) (c:txtexp))
(command "_layer" "set" "nitride" "")
(command "_layer" "set" "text" "")
(command-s "_text" "3808.868,963.3" "2" "-90" "nominal: 150" )
(sssetfirst nil (ssget "_L"))
(if (not (numberp (vl-string-search "Mac" (getvar "platform")))) (c:txtexp))
(command "_layer" "set" "nitride" "")
(command "_layer" "set" "indicators" "")
(setq coords (list 
(list 3760.415 940) 
(list 3760.415 920) 
(list 3740.415 900) 
(list 3760.415 880) 
(list 3760.415 860) 
(list 3760.415 900) 
(list 3760.415 887.0711) 
(list 3747.4861 900) 
(list 3760.415 912.9289) 
(list 3760.415 900)))
(apply 'command (append '("pline") coords '("c")))
(command "._fillet" "radius" "1" "._fillet" "P" (entlast))
(setq coords (list 
(list 3919.585 940) 
(list 3919.585 920) 
(list 3939.585 900) 
(list 3919.585 880) 
(list 3919.585 860) 
(list 3919.585 900) 
(list 3919.585 887.0711) 
(list 3932.5139 900) 
(list 3919.585 912.9289) 
(list 3919.585 900)))
(apply 'command (append '("pline") coords '("c")))
(command "._fillet" "radius" "1" "._fillet" "P" (entlast))
(command "_layer" "set" "holes" "")
(command "_circle" "3758.0629,914.1124" "0.5")
(command "_circle" "3755.7109,911.7603" "0.5")
(command "_circle" "3753.3588,909.4083" "0.5")
(command "_circle" "3751.0067,907.0562" "0.5")
(command "_circle" "3748.6547,904.7041" "0.5")
(command "_circle" "3746.3026,902.3521" "0.5")
(command "_circle" "3743.9505,900" "0.5")
(command "_circle" "3746.3026,897.6479" "0.5")
(command "_circle" "3748.6547,895.2959" "0.5")
(command "_circle" "3751.0067,892.9438" "0.5")
(command "_circle" "3753.3588,890.5917" "0.5")
(command "_circle" "3755.7109,888.2397" "0.5")
(command "_circle" "3758.0629,885.8876" "0.5")
(command "_circle" "3921.9371,914.1124" "0.5")
(command "_circle" "3924.2891,911.7603" "0.5")
(command "_circle" "3926.6412,909.4083" "0.5")
(command "_circle" "3928.9933,907.0562" "0.5")
(command "_circle" "3931.3453,904.7041" "0.5")
(command "_circle" "3933.6974,902.3521" "0.5")
(command "_circle" "3936.0495,900" "0.5")
(command "_circle" "3933.6974,897.6479" "0.5")
(command "_circle" "3931.3453,895.2959" "0.5")
(command "_circle" "3928.9933,892.9438" "0.5")
(command "_circle" "3926.6412,890.5917" "0.5")
(command "_circle" "3924.2891,888.2397" "0.5")
(command "_circle" "3921.9371,885.8876" "0.5")
(command "_layer" "set" "nitride" "")
(command "_block" "blkcoupler12" "3840,900" coupler12 "")
(command "_insert" "blkcoupler12" "3840,900" "1" "1" "0")
(command "_insert" "blkcoupler12" "3840,900" "1" "1" "180")
(command "_block" "blksinglenanobeam12" "3840,900" singlenanobeam12 "")
(command "_insert" "blksinglenanobeam12" "3840,900" "1" "1" "0")
(command "_insert" "blksinglenanobeam12" "3840,900" "1" "1" "180")
(command "_block" "blkanglednodearray12" "3840,900" anglednodearray12 "")
(command "_insert" "blkanglednodearray12" "3840,900" "1" "1" "0")
(command "_insert" "blkanglednodearray12" "3840,900" "1" "1" "180")
(command "_block" "blkcooledsinglenanobeam12" "3840,900" cooledsinglenanobeam12 "")
(command "_insert" "blkcooledsinglenanobeam12" "3840,900" "1" "1" "0")
(command "_insert" "blkcooledsinglenanobeam12" "3840,900" "1" "1" "180")
(command "_block" "blkyjunction12" "3840,900" yjunction12 "")
(command "_insert" "blkyjunction12" "3840,900" "1" "1" "0")
(command "_insert" "blkyjunction12" "3840,900" "1" "1" "180")
; DRAWING BULGING VEE GROOVE
(command "_layer" "set" "vgroove" "")
(setq coords (list 
(list 3765.415 -605) 
(list 3765.415 0) 
(list 3765.415 0) 
(list 3765.415 1800) 
(list 3765.415 1800) 
(list 3765.415 2405) 
(list 3914.585 2405) 
(list 3914.585 1800) 
(list 3914.585 1800) 
(list 3914.585 0) 
(list 3914.585 0) 
(list 3914.585 -605)))
(apply 'command (append '("pline") coords '("c")))
(command "._fillet" "radius" "0" "._fillet" "P" (entlast))
(command "_layer" "set" "window" "")
(command "_rectangle" "3765.415,-1935" "3914.585,-600")
(command "_rectangle" "3765.415,2400" "3914.585,5300")
(command "_layer" "set" "grid" "")
(command "_rectangle" "3766.415,-1934" "3789.9433,-1909.2133")
(command "_array" "last" "" "R" "75" "3" "25.7867" "24.5283")
(command "_rectangle" "3841,-1934" "3864.5283,-1909.2133")
(command "_array" "last" "" "R" "75" "3" "25.7867" "24.5283")
(command "_rectangle" "3766.415,1" "3789.9433,25.7")
(command "_array" "last" "" "R" "70" "3" "25.7" "24.5283")
(command "_rectangle" "3841,1" "3864.5283,25.7")
(command "_array" "last" "" "R" "70" "3" "25.7" "24.5283")
(command "_rectangle" "3766.415,1801" "3789.9433,1825.9185")
(command "_array" "last" "" "R" "135" "3" "25.9185" "24.5283")
(command "_rectangle" "3841,1801" "3864.5283,1825.9185")
(command "_array" "last" "" "R" "135" "3" "25.9185" "24.5283")
(command "_layer" "set" "vgrooveFDA" "")
(command "_rectangle" "3914.585,-2233" "3765.415,-1933")
(command "_layer" "set" "nitride" "")
(command "_layer" "set" "holes" "")
(command "_circle" "3917.085,331.5" "0.5")
(command "_array" "last" "" "R" "379" "1" "3" "2.5")
(command "_circle" "3762.915,331.5" "0.5")
(command "_array" "last" "" "R" "379" "1" "3" "-2.5")
(command "_layer" "set" "nitride" "")
(command "_layer" "set" "window" "")
(command "_layer" "set" "window" "")
(command "_rectangle" "3919.585,0" "4080.415,1800")
(command "._fillet" "radius" "20" "._fillet" "P" (entlast))
(command "_layer" "set" "grid" "")
(command "_rectangle" "3920.585,1" "3942.4179,25.7")
(command "_array" "last" "" "R" "70" "7" "25.7" "22.8329")
(command "_layer" "set" "nitride" "")
; DRAWING REGION LAYER
(command "_layer" "set" "regionLayer12" "")
(command "_rectangle" "3760,-460" "3920,2260")
(command "_layer" "set" "nitride" "")
(setq coupler12 nil)
(setq singlenanobeam12 nil)
(setq anglednodearray12 nil)
(setq cooledsinglenanobeam12 nil)
(setq yjunction12 nil)
; DEVICE #13
(command "_layer" "set" "window" "")
(command "_circle" "4072.915,-415" "5")
(command "_circle" "4072.915,-402.5" "5")
(command "_circle" "4072.915,-390" "5")
(command "_circle" "4072.915,-377.5" "5")
(command "_circle" "4060.415,-415" "5")
(command "_circle" "4060.415,-402.5" "5")
(command "_circle" "4060.415,-390" "5")
(command "_circle" "4060.415,-377.5" "5")
(command "_circle" "4047.915,-415" "5")
(command "_circle" "4047.915,-402.5" "5")
(command "_circle" "4047.915,-390" "5")
(command "_circle" "4047.915,-377.5" "5")
(command "_circle" "4035.415,-415" "5")
(command "_layer" "set" "nitride" "")
(setq currobj nil)
(setq currobj (ssadd))
; DRAWING COUPLER
(setq coords (list 
(list 4160.0615 -415) 
(list 4160.0615 -413) 
(list 4233.585 -413) 
(list 4233.585 -413) 
(list 4233.9677 -413.0761) 
(list 4234.2921 -413.2929) 
(list 4234.5089 -413.6173) 
(list 4234.585 -414) 
(list 4234.585 -411.8) 
(list 4234.585 -411.8) 
(list 4234.5089 -412.1827) 
(list 4234.2921 -412.5071) 
(list 4233.9677 -412.7239) 
(list 4233.585 -412.8) 
(list 4160.0615 -412.8) 
(list 4160.0615 -410.8) 
(list 4159.9385 -410.8) 
(list 4159.9385 -412.8) 
(list 4086.415 -412.8) 
(list 4086.0323 -412.7239) 
(list 4085.7079 -412.5071) 
(list 4085.4911 -412.1827) 
(list 4085.415 -411.8) 
(list 4085.415 -411.8) 
(list 4085.415 -414) 
(list 4085.4911 -413.6173) 
(list 4085.7079 -413.2929) 
(list 4086.0323 -413.0761) 
(list 4086.415 -413) 
(list 4086.415 -413) 
(list 4159.9385 -413) 
(list 4159.9385 -415)))
(apply 'command (append '("pline") coords '("c")))
(setq currobj (ssadd (entlast) currobj))
(command "._fillet" "radius" "0.3" "._fillet" "P" (entlast))
(command "_layer" "set" "holes" "")
(command "_circle" "4160,-412.9" "0.113")
(setq currobj (ssadd (entlast) currobj))
(command "_layer" "set" "nitride" "")
(command "_layer" "set" "text" "")
(command "_circle" "4159.2,-415" "0.075")
(command "_circle" "4159.2,-414.7" "0.075")
(command "_circle" "4159.2,-414.4" "0.075")
(command "_circle" "4158.9,-415" "0.075")
(command "_circle" "4158.9,-414.7" "0.075")
(command "_circle" "4158.9,-414.4" "0.075")
(command "_circle" "4158.6,-415" "0.075")
(command "_circle" "4158.6,-414.7" "0.075")
(command "_circle" "4158.6,-414.4" "0.075")
(command "_layer" "set" "nitride" "")
(command "_layer" "set" "prebias" "")
(command "_rectangle" "4085.415,-414" "4234.585,-411.8")
(setq currobj (ssadd (entlast) currobj))
(command "_rectangle" "4159.9385,-415" "4160.0615,-410.8")
(setq currobj (ssadd (entlast) currobj))
(command "_layer" "set" "nitride" "")
(setq coupler13 currobj)
(setq currobj nil)
(setq currobj (ssadd))
; DRAWING SINGLE NANOBEAM
(setq coords (list 
(list 4160.0615 -410.8) 
(list 4160.0615 -409.1417) 
(list 4160.0615 -407.4833) 
(list 4160.0615 -405.825) 
(list 4160.0615 -404.1667) 
(list 4160.0615 -402.5083) 
(list 4160.0615 -400.85) 
(list 4160.0615 -399.1917) 
(list 4160.0615 -397.5333) 
(list 4160.0616 -395.875) 
(list 4160.0616 -394.2167) 
(list 4160.0616 -392.5583) 
(list 4160.0616 -390.9) 
(list 4160.0617 -389.2417) 
(list 4160.0617 -387.5833) 
(list 4160.0617 -385.925) 
(list 4160.0618 -384.2667) 
(list 4160.0619 -382.6083) 
(list 4160.0619 -380.95) 
(list 4160.062 -379.2917) 
(list 4160.0621 -377.6333) 
(list 4160.0622 -375.975) 
(list 4160.0623 -374.3167) 
(list 4160.0624 -372.6583) 
(list 4160.0625 -371) 
(list 4160.0626 -369.3417) 
(list 4160.0628 -367.6833) 
(list 4160.0629 -366.025) 
(list 4160.0631 -364.3667) 
(list 4160.0632 -362.7083) 
(list 4160.0634 -361.05) 
(list 4160.0636 -359.3917) 
(list 4160.0638 -357.7333) 
(list 4160.0641 -356.075) 
(list 4160.0643 -354.4167) 
(list 4160.0646 -352.7583) 
(list 4160.0648 -351.1) 
(list 4160.0651 -349.4417) 
(list 4160.0654 -347.7833) 
(list 4160.0657 -346.125) 
(list 4160.0661 -344.4667) 
(list 4160.0664 -342.8083) 
(list 4160.0668 -341.15) 
(list 4160.0672 -339.4917) 
(list 4160.0676 -337.8333) 
(list 4160.068 -336.175) 
(list 4160.0685 -334.5167) 
(list 4160.0689 -332.8583) 
(list 4160.0694 -331.2) 
(list 4160.0699 -329.5417) 
(list 4160.0704 -327.8833) 
(list 4160.071 -326.225) 
(list 4160.0715 -324.5667) 
(list 4160.0721 -322.9083) 
(list 4160.0728 -321.25) 
(list 4160.0734 -319.5917) 
(list 4160.0741 -317.9333) 
(list 4160.0747 -316.275) 
(list 4160.0754 -314.6167) 
(list 4160.0762 -312.9583) 
(list 4160.0769 -311.3) 
(list 4160.0777 -309.6417) 
(list 4160.0785 -307.9833) 
(list 4160.0794 -306.325) 
(list 4160.0802 -304.6667) 
(list 4160.0811 -303.0083) 
(list 4160.082 -301.35) 
(list 4160.083 -299.6917) 
(list 4160.084 -298.0333) 
(list 4160.085 -296.375) 
(list 4160.086 -294.7167) 
(list 4160.0871 -293.0583) 
(list 4160.0882 -291.4) 
(list 4160.0893 -289.7417) 
(list 4160.0905 -288.0833) 
(list 4160.0917 -286.425) 
(list 4160.0929 -284.7667) 
(list 4160.0941 -283.1083) 
(list 4160.0954 -281.45) 
(list 4160.0967 -279.7917) 
(list 4160.0981 -278.1333) 
(list 4160.0995 -276.475) 
(list 4160.1009 -274.8167) 
(list 4160.1024 -273.1583) 
(list 4160.1039 -271.5) 
(list 4160.1054 -269.8417) 
(list 4160.107 -268.1833) 
(list 4160.1086 -266.525) 
(list 4160.1102 -264.8667) 
(list 4160.1119 -263.2083) 
(list 4160.1136 -261.55) 
(list 4160.1154 -259.8917) 
(list 4160.1172 -258.2333) 
(list 4160.119 -256.575) 
(list 4160.1209 -254.9167) 
(list 4160.1228 -253.2583) 
(list 4160.1247 -251.6) 
(list 4160.1267 -249.9417) 
(list 4160.1288 -248.2833) 
(list 4160.1308 -246.625) 
(list 4160.133 -244.9667) 
(list 4160.1351 -243.3083) 
(list 4160.1373 -241.65) 
(list 4160.1396 -239.9917) 
(list 4160.1419 -238.3333) 
(list 4160.1442 -236.675) 
(list 4160.1466 -235.0167) 
(list 4160.1491 -233.3583) 
(list 4160.1515 -231.7) 
(list 4160.1541 -230.0417) 
(list 4160.1566 -228.3833) 
(list 4160.1592 -226.725) 
(list 4160.1619 -225.0667) 
(list 4160.1646 -223.4083) 
(list 4160.1674 -221.75) 
(list 4160.1702 -220.0917) 
(list 4160.1731 -218.4333) 
(list 4160.176 -216.775) 
(list 4160.1789 -215.1167) 
(list 4160.1819 -213.4583) 
(list 4160.185 -211.8) 
(list 4159.815 -211.8) 
(list 4159.8181 -213.4583) 
(list 4159.8211 -215.1167) 
(list 4159.824 -216.775) 
(list 4159.8269 -218.4333) 
(list 4159.8298 -220.0917) 
(list 4159.8326 -221.75) 
(list 4159.8354 -223.4083) 
(list 4159.8381 -225.0667) 
(list 4159.8408 -226.725) 
(list 4159.8434 -228.3833) 
(list 4159.8459 -230.0417) 
(list 4159.8485 -231.7) 
(list 4159.8509 -233.3583) 
(list 4159.8534 -235.0167) 
(list 4159.8558 -236.675) 
(list 4159.8581 -238.3333) 
(list 4159.8604 -239.9917) 
(list 4159.8627 -241.65) 
(list 4159.8649 -243.3083) 
(list 4159.867 -244.9667) 
(list 4159.8692 -246.625) 
(list 4159.8712 -248.2833) 
(list 4159.8733 -249.9417) 
(list 4159.8753 -251.6) 
(list 4159.8772 -253.2583) 
(list 4159.8791 -254.9167) 
(list 4159.881 -256.575) 
(list 4159.8828 -258.2333) 
(list 4159.8846 -259.8917) 
(list 4159.8864 -261.55) 
(list 4159.8881 -263.2083) 
(list 4159.8898 -264.8667) 
(list 4159.8914 -266.525) 
(list 4159.893 -268.1833) 
(list 4159.8946 -269.8417) 
(list 4159.8961 -271.5) 
(list 4159.8976 -273.1583) 
(list 4159.8991 -274.8167) 
(list 4159.9005 -276.475) 
(list 4159.9019 -278.1333) 
(list 4159.9033 -279.7917) 
(list 4159.9046 -281.45) 
(list 4159.9059 -283.1083) 
(list 4159.9071 -284.7667) 
(list 4159.9083 -286.425) 
(list 4159.9095 -288.0833) 
(list 4159.9107 -289.7417) 
(list 4159.9118 -291.4) 
(list 4159.9129 -293.0583) 
(list 4159.914 -294.7167) 
(list 4159.915 -296.375) 
(list 4159.916 -298.0333) 
(list 4159.917 -299.6917) 
(list 4159.918 -301.35) 
(list 4159.9189 -303.0083) 
(list 4159.9198 -304.6667) 
(list 4159.9206 -306.325) 
(list 4159.9215 -307.9833) 
(list 4159.9223 -309.6417) 
(list 4159.9231 -311.3) 
(list 4159.9238 -312.9583) 
(list 4159.9246 -314.6167) 
(list 4159.9253 -316.275) 
(list 4159.9259 -317.9333) 
(list 4159.9266 -319.5917) 
(list 4159.9272 -321.25) 
(list 4159.9279 -322.9083) 
(list 4159.9285 -324.5667) 
(list 4159.929 -326.225) 
(list 4159.9296 -327.8833) 
(list 4159.9301 -329.5417) 
(list 4159.9306 -331.2) 
(list 4159.9311 -332.8583) 
(list 4159.9315 -334.5167) 
(list 4159.932 -336.175) 
(list 4159.9324 -337.8333) 
(list 4159.9328 -339.4917) 
(list 4159.9332 -341.15) 
(list 4159.9336 -342.8083) 
(list 4159.9339 -344.4667) 
(list 4159.9343 -346.125) 
(list 4159.9346 -347.7833) 
(list 4159.9349 -349.4417) 
(list 4159.9352 -351.1) 
(list 4159.9354 -352.7583) 
(list 4159.9357 -354.4167) 
(list 4159.9359 -356.075) 
(list 4159.9362 -357.7333) 
(list 4159.9364 -359.3917) 
(list 4159.9366 -361.05) 
(list 4159.9368 -362.7083) 
(list 4159.9369 -364.3667) 
(list 4159.9371 -366.025) 
(list 4159.9372 -367.6833) 
(list 4159.9374 -369.3417) 
(list 4159.9375 -371) 
(list 4159.9376 -372.6583) 
(list 4159.9377 -374.3167) 
(list 4159.9378 -375.975) 
(list 4159.9379 -377.6333) 
(list 4159.938 -379.2917) 
(list 4159.9381 -380.95) 
(list 4159.9381 -382.6083) 
(list 4159.9382 -384.2667) 
(list 4159.9383 -385.925) 
(list 4159.9383 -387.5833) 
(list 4159.9383 -389.2417) 
(list 4159.9384 -390.9) 
(list 4159.9384 -392.5583) 
(list 4159.9384 -394.2167) 
(list 4159.9384 -395.875) 
(list 4159.9385 -397.5333) 
(list 4159.9385 -399.1917) 
(list 4159.9385 -400.85) 
(list 4159.9385 -402.5083) 
(list 4159.9385 -404.1667) 
(list 4159.9385 -405.825) 
(list 4159.9385 -407.4833) 
(list 4159.9385 -409.1417) 
(list 4159.9385 -410.8)))
(apply 'command (append '("pline") coords '("c")))
(setq currobj (ssadd (entlast) currobj))
(command "_layer" "set" "prebias" "")
(command "_rectangle" "4159.815,-410.8" "4160.185,-211.8")
(setq currobj (ssadd (entlast) currobj))
(command "_layer" "set" "nitride" "")
(setq singlenanobeam13 currobj)
(setq currobj nil)
(setq currobj (ssadd))
; DRAWING NODE ARRAY
(setq coords (list 
(list 4160.185 -211.8) 
(list 4160.5625 -201.8) 
(list 4160.5625 -201.8) 
(list 4160.5625 -200.8) 
(list 4234.585 -212.6864) 
(list 4234.585 -207.7434) 
(list 4160.5625 -197.357) 
(list 4160.5625 -196.357) 
(list 4160.5625 -196.357) 
(list 4160.2625 -186.357) 
(list 4159.7375 -186.357) 
(list 4159.4375 -196.357) 
(list 4159.4375 -196.357) 
(list 4159.4375 -197.357) 
(list 4085.415 -207.7434) 
(list 4085.415 -212.6864) 
(list 4159.4375 -200.8) 
(list 4159.4375 -201.8) 
(list 4159.4375 -201.8) 
(list 4159.815 -211.8)))
(apply 'command (append '("pline") coords '("c")))
(setq currobj (ssadd (entlast) currobj))
(command "_layer" "set" "prebias" "")
(setq coords (list 
(list 4159.4375 -212.6864) 
(list 4159.4375 -200.8) 
(list 4085.415 -212.6864) 
(list 4085.415 -207.7434) 
(list 4159.4375 -197.357) 
(list 4159.4375 -186.357) 
(list 4160.5625 -186.357) 
(list 4160.5625 -197.357) 
(list 4234.585 -207.7434) 
(list 4234.585 -212.6864) 
(list 4160.5625 -200.8) 
(list 4160.5625 -212.6864)))
(apply 'command (append '("pline") coords '("c")))
(setq currobj (ssadd (entlast) currobj))
(command "_layer" "set" "nitride" "")
(command "_layer" "set" "fda1" "")
(setq coords (list 
(list 4160.5625 -200.657) 
(list 4234.585 -212.5434) 
(list 4234.585 -212.3664) 
(list 4160.5625 -200.58)))
(apply 'command (append '("pline") coords '("c")))
(setq currobj (ssadd (entlast) currobj))
(setq coords (list 
(list 4160.5625 -200.437) 
(list 4234.585 -212.2234) 
(list 4234.585 -212.0464) 
(list 4160.5625 -200.36)))
(apply 'command (append '("pline") coords '("c")))
(setq currobj (ssadd (entlast) currobj))
(setq coords (list 
(list 4160.5625 -200.217) 
(list 4234.585 -211.9034) 
(list 4234.585 -211.7264) 
(list 4160.5625 -200.14)))
(apply 'command (append '("pline") coords '("c")))
(setq currobj (ssadd (entlast) currobj))
(setq coords (list 
(list 4160.5625 -199.997) 
(list 4234.585 -211.5834) 
(list 4234.585 -211.4064) 
(list 4160.5625 -199.92)))
(apply 'command (append '("pline") coords '("c")))
(setq currobj (ssadd (entlast) currobj))
(setq coords (list 
(list 4160.5625 -199.777) 
(list 4234.585 -211.2634) 
(list 4234.585 -211.0864) 
(list 4160.5625 -199.7)))
(apply 'command (append '("pline") coords '("c")))
(setq currobj (ssadd (entlast) currobj))
(setq coords (list 
(list 4160.5625 -199.557) 
(list 4234.585 -210.9434) 
(list 4234.585 -210.7664) 
(list 4160.5625 -199.48)))
(apply 'command (append '("pline") coords '("c")))
(setq currobj (ssadd (entlast) currobj))
(setq coords (list 
(list 4160.5625 -199.337) 
(list 4234.585 -210.6234) 
(list 4234.585 -210.4464) 
(list 4160.5625 -199.26)))
(apply 'command (append '("pline") coords '("c")))
(setq currobj (ssadd (entlast) currobj))
(setq coords (list 
(list 4160.5625 -199.117) 
(list 4234.585 -210.3034) 
(list 4234.585 -210.1264) 
(list 4160.5625 -199.04)))
(apply 'command (append '("pline") coords '("c")))
(setq currobj (ssadd (entlast) currobj))
(setq coords (list 
(list 4160.5625 -198.897) 
(list 4234.585 -209.9834) 
(list 4234.585 -209.8064) 
(list 4160.5625 -198.82)))
(apply 'command (append '("pline") coords '("c")))
(setq currobj (ssadd (entlast) currobj))
(setq coords (list 
(list 4160.5625 -198.677) 
(list 4234.585 -209.6634) 
(list 4234.585 -209.4864) 
(list 4160.5625 -198.6)))
(apply 'command (append '("pline") coords '("c")))
(setq currobj (ssadd (entlast) currobj))
(setq coords (list 
(list 4160.5625 -198.457) 
(list 4234.585 -209.3434) 
(list 4234.585 -209.1664) 
(list 4160.5625 -198.38)))
(apply 'command (append '("pline") coords '("c")))
(setq currobj (ssadd (entlast) currobj))
(setq coords (list 
(list 4160.5625 -198.237) 
(list 4234.585 -209.0234) 
(list 4234.585 -208.8464) 
(list 4160.5625 -198.16)))
(apply 'command (append '("pline") coords '("c")))
(setq currobj (ssadd (entlast) currobj))
(setq coords (list 
(list 4160.5625 -198.017) 
(list 4234.585 -208.7034) 
(list 4234.585 -208.5264) 
(list 4160.5625 -197.94)))
(apply 'command (append '("pline") coords '("c")))
(setq currobj (ssadd (entlast) currobj))
(setq coords (list 
(list 4160.5625 -197.797) 
(list 4234.585 -208.3834) 
(list 4234.585 -208.2064) 
(list 4160.5625 -197.72)))
(apply 'command (append '("pline") coords '("c")))
(setq currobj (ssadd (entlast) currobj))
(setq coords (list 
(list 4160.5625 -197.577) 
(list 4234.585 -208.0634) 
(list 4234.585 -207.8864) 
(list 4160.5625 -197.5)))
(apply 'command (append '("pline") coords '("c")))
(setq currobj (ssadd (entlast) currobj))
(setq coords (list 
(list 4159.4375 -197.5) 
(list 4085.415 -207.8864) 
(list 4085.415 -208.0634) 
(list 4159.4375 -197.577)))
(apply 'command (append '("pline") coords '("c")))
(setq currobj (ssadd (entlast) currobj))
(setq coords (list 
(list 4159.4375 -197.72) 
(list 4085.415 -208.2064) 
(list 4085.415 -208.3834) 
(list 4159.4375 -197.797)))
(apply 'command (append '("pline") coords '("c")))
(setq currobj (ssadd (entlast) currobj))
(setq coords (list 
(list 4159.4375 -197.94) 
(list 4085.415 -208.5264) 
(list 4085.415 -208.7034) 
(list 4159.4375 -198.017)))
(apply 'command (append '("pline") coords '("c")))
(setq currobj (ssadd (entlast) currobj))
(setq coords (list 
(list 4159.4375 -198.16) 
(list 4085.415 -208.8464) 
(list 4085.415 -209.0234) 
(list 4159.4375 -198.237)))
(apply 'command (append '("pline") coords '("c")))
(setq currobj (ssadd (entlast) currobj))
(setq coords (list 
(list 4159.4375 -198.38) 
(list 4085.415 -209.1664) 
(list 4085.415 -209.3434) 
(list 4159.4375 -198.457)))
(apply 'command (append '("pline") coords '("c")))
(setq currobj (ssadd (entlast) currobj))
(setq coords (list 
(list 4159.4375 -198.6) 
(list 4085.415 -209.4864) 
(list 4085.415 -209.6634) 
(list 4159.4375 -198.677)))
(apply 'command (append '("pline") coords '("c")))
(setq currobj (ssadd (entlast) currobj))
(setq coords (list 
(list 4159.4375 -198.82) 
(list 4085.415 -209.8064) 
(list 4085.415 -209.9834) 
(list 4159.4375 -198.897)))
(apply 'command (append '("pline") coords '("c")))
(setq currobj (ssadd (entlast) currobj))
(setq coords (list 
(list 4159.4375 -199.04) 
(list 4085.415 -210.1264) 
(list 4085.415 -210.3034) 
(list 4159.4375 -199.117)))
(apply 'command (append '("pline") coords '("c")))
(setq currobj (ssadd (entlast) currobj))
(setq coords (list 
(list 4159.4375 -199.26) 
(list 4085.415 -210.4464) 
(list 4085.415 -210.6234) 
(list 4159.4375 -199.337)))
(apply 'command (append '("pline") coords '("c")))
(setq currobj (ssadd (entlast) currobj))
(setq coords (list 
(list 4159.4375 -199.48) 
(list 4085.415 -210.7664) 
(list 4085.415 -210.9434) 
(list 4159.4375 -199.557)))
(apply 'command (append '("pline") coords '("c")))
(setq currobj (ssadd (entlast) currobj))
(setq coords (list 
(list 4159.4375 -199.7) 
(list 4085.415 -211.0864) 
(list 4085.415 -211.2634) 
(list 4159.4375 -199.777)))
(apply 'command (append '("pline") coords '("c")))
(setq currobj (ssadd (entlast) currobj))
(setq coords (list 
(list 4159.4375 -199.92) 
(list 4085.415 -211.4064) 
(list 4085.415 -211.5834) 
(list 4159.4375 -199.997)))
(apply 'command (append '("pline") coords '("c")))
(setq currobj (ssadd (entlast) currobj))
(setq coords (list 
(list 4159.4375 -200.14) 
(list 4085.415 -211.7264) 
(list 4085.415 -211.9034) 
(list 4159.4375 -200.217)))
(apply 'command (append '("pline") coords '("c")))
(setq currobj (ssadd (entlast) currobj))
(setq coords (list 
(list 4159.4375 -200.36) 
(list 4085.415 -212.0464) 
(list 4085.415 -212.2234) 
(list 4159.4375 -200.437)))
(apply 'command (append '("pline") coords '("c")))
(setq currobj (ssadd (entlast) currobj))
(setq coords (list 
(list 4159.4375 -200.58) 
(list 4085.415 -212.3664) 
(list 4085.415 -212.5434) 
(list 4159.4375 -200.657)))
(apply 'command (append '("pline") coords '("c")))
(setq currobj (ssadd (entlast) currobj))
(command "_layer" "set" "nitride" "")
(command "_layer" "set" "text" "")
(command "_circle" "4158.985,-211.8" "0.075")
(command "_circle" "4158.985,-211.5" "0.075")
(command "_circle" "4158.985,-211.2" "0.075")
(command "_circle" "4158.985,-210.9" "0.075")
(command "_circle" "4158.985,-210.6" "0.075")
(command "_circle" "4158.685,-211.8" "0.075")
(command "_circle" "4158.685,-211.5" "0.075")
(command "_circle" "4158.685,-211.2" "0.075")
(command "_circle" "4158.685,-210.9" "0.075")
(command "_circle" "4158.685,-210.6" "0.075")
(command "_circle" "4158.385,-211.8" "0.075")
(command "_circle" "4158.385,-211.5" "0.075")
(command "_circle" "4158.385,-211.2" "0.075")
(command "_circle" "4158.385,-210.9" "0.075")
(command "_circle" "4158.385,-210.6" "0.075")
(command "_circle" "4158.085,-211.8" "0.075")
(command "_circle" "4158.085,-211.5" "0.075")
(command "_circle" "4158.085,-211.2" "0.075")
(command "_circle" "4158.085,-210.9" "0.075")
(command "_circle" "4158.085,-210.6" "0.075")
(command "_circle" "4157.785,-211.8" "0.075")
(command "_circle" "4157.785,-211.5" "0.075")
(command "_circle" "4157.785,-211.2" "0.075")
(command "_circle" "4157.785,-210.9" "0.075")
(command "_circle" "4157.785,-210.6" "0.075")
(command "_layer" "set" "nitride" "")
(setq anglednodearray13 currobj)
(setq currobj nil)
(setq currobj (ssadd))
; DRAWING COOLED SINGLE NANOBEAM
(setq coords (list 
(list 4160.2625 -186.357) 
(list 4160.2625 -181.357) 
(list 4159.7375 -181.357) 
(list 4159.7375 -186.357)))
(apply 'command (append '("pline") coords '("c")))
(setq currobj (ssadd (entlast) currobj))
(command "_layer" "set" "prebias" "")
(command "_rectangle" "4159.7375,-186.357" "4160.2625,-181.357")
(setq currobj (ssadd (entlast) currobj))
(command "_layer" "set" "nitride" "")
(setq coords (list 
(list 4160.2625 -181.357) 
(list 4160.5625 -171.357) 
(list 4160.5625 -171.357) 
(list 4160.5625 -170.357) 
(list 4234.585 -171.107) 
(list 4234.585 -166.164) 
(list 4160.5625 -166.914) 
(list 4160.5625 -165.914) 
(list 4160.5625 -165.914) 
(list 4160.2625 -155.914) 
(list 4159.7375 -155.914) 
(list 4159.4375 -165.914) 
(list 4159.4375 -165.914) 
(list 4159.4375 -166.914) 
(list 4085.415 -166.164) 
(list 4085.415 -171.107) 
(list 4159.4375 -170.357) 
(list 4159.4375 -171.357) 
(list 4159.4375 -171.357) 
(list 4159.7375 -181.357)))
(apply 'command (append '("pline") coords '("c")))
(setq currobj (ssadd (entlast) currobj))
(command "_layer" "set" "prebias" "")
(setq coords (list 
(list 4159.4375 -181.357) 
(list 4159.4375 -170.357) 
(list 4085.415 -171.107) 
(list 4085.415 -166.164) 
(list 4159.4375 -166.914) 
(list 4159.4375 -155.914) 
(list 4160.5625 -155.914) 
(list 4160.5625 -166.914) 
(list 4234.585 -166.164) 
(list 4234.585 -171.107) 
(list 4160.5625 -170.357) 
(list 4160.5625 -181.357)))
(apply 'command (append '("pline") coords '("c")))
(setq currobj (ssadd (entlast) currobj))
(command "_layer" "set" "nitride" "")
(command "_layer" "set" "fda1" "")
(setq coords (list 
(list 4160.5625 -170.214) 
(list 4234.585 -170.964) 
(list 4234.585 -170.787) 
(list 4160.5625 -170.137)))
(apply 'command (append '("pline") coords '("c")))
(setq currobj (ssadd (entlast) currobj))
(setq coords (list 
(list 4160.5625 -169.994) 
(list 4234.585 -170.644) 
(list 4234.585 -170.467) 
(list 4160.5625 -169.917)))
(apply 'command (append '("pline") coords '("c")))
(setq currobj (ssadd (entlast) currobj))
(setq coords (list 
(list 4160.5625 -169.774) 
(list 4234.585 -170.324) 
(list 4234.585 -170.147) 
(list 4160.5625 -169.697)))
(apply 'command (append '("pline") coords '("c")))
(setq currobj (ssadd (entlast) currobj))
(setq coords (list 
(list 4160.5625 -169.554) 
(list 4234.585 -170.004) 
(list 4234.585 -169.827) 
(list 4160.5625 -169.477)))
(apply 'command (append '("pline") coords '("c")))
(setq currobj (ssadd (entlast) currobj))
(setq coords (list 
(list 4160.5625 -169.334) 
(list 4234.585 -169.684) 
(list 4234.585 -169.507) 
(list 4160.5625 -169.257)))
(apply 'command (append '("pline") coords '("c")))
(setq currobj (ssadd (entlast) currobj))
(setq coords (list 
(list 4160.5625 -169.114) 
(list 4234.585 -169.364) 
(list 4234.585 -169.187) 
(list 4160.5625 -169.037)))
(apply 'command (append '("pline") coords '("c")))
(setq currobj (ssadd (entlast) currobj))
(setq coords (list 
(list 4160.5625 -168.894) 
(list 4234.585 -169.044) 
(list 4234.585 -168.867) 
(list 4160.5625 -168.817)))
(apply 'command (append '("pline") coords '("c")))
(setq currobj (ssadd (entlast) currobj))
(setq coords (list 
(list 4160.5625 -168.674) 
(list 4234.585 -168.724) 
(list 4234.585 -168.547) 
(list 4160.5625 -168.597)))
(apply 'command (append '("pline") coords '("c")))
(setq currobj (ssadd (entlast) currobj))
(setq coords (list 
(list 4160.5625 -168.454) 
(list 4234.585 -168.404) 
(list 4234.585 -168.227) 
(list 4160.5625 -168.377)))
(apply 'command (append '("pline") coords '("c")))
(setq currobj (ssadd (entlast) currobj))
(setq coords (list 
(list 4160.5625 -168.234) 
(list 4234.585 -168.084) 
(list 4234.585 -167.907) 
(list 4160.5625 -168.157)))
(apply 'command (append '("pline") coords '("c")))
(setq currobj (ssadd (entlast) currobj))
(setq coords (list 
(list 4160.5625 -168.014) 
(list 4234.585 -167.764) 
(list 4234.585 -167.587) 
(list 4160.5625 -167.937)))
(apply 'command (append '("pline") coords '("c")))
(setq currobj (ssadd (entlast) currobj))
(setq coords (list 
(list 4160.5625 -167.794) 
(list 4234.585 -167.444) 
(list 4234.585 -167.267) 
(list 4160.5625 -167.717)))
(apply 'command (append '("pline") coords '("c")))
(setq currobj (ssadd (entlast) currobj))
(setq coords (list 
(list 4160.5625 -167.574) 
(list 4234.585 -167.124) 
(list 4234.585 -166.947) 
(list 4160.5625 -167.497)))
(apply 'command (append '("pline") coords '("c")))
(setq currobj (ssadd (entlast) currobj))
(setq coords (list 
(list 4160.5625 -167.354) 
(list 4234.585 -166.804) 
(list 4234.585 -166.627) 
(list 4160.5625 -167.277)))
(apply 'command (append '("pline") coords '("c")))
(setq currobj (ssadd (entlast) currobj))
(setq coords (list 
(list 4160.5625 -167.134) 
(list 4234.585 -166.484) 
(list 4234.585 -166.307) 
(list 4160.5625 -167.057)))
(apply 'command (append '("pline") coords '("c")))
(setq currobj (ssadd (entlast) currobj))
(setq coords (list 
(list 4159.4375 -167.057) 
(list 4085.415 -166.307) 
(list 4085.415 -166.484) 
(list 4159.4375 -167.134)))
(apply 'command (append '("pline") coords '("c")))
(setq currobj (ssadd (entlast) currobj))
(setq coords (list 
(list 4159.4375 -167.277) 
(list 4085.415 -166.627) 
(list 4085.415 -166.804) 
(list 4159.4375 -167.354)))
(apply 'command (append '("pline") coords '("c")))
(setq currobj (ssadd (entlast) currobj))
(setq coords (list 
(list 4159.4375 -167.497) 
(list 4085.415 -166.947) 
(list 4085.415 -167.124) 
(list 4159.4375 -167.574)))
(apply 'command (append '("pline") coords '("c")))
(setq currobj (ssadd (entlast) currobj))
(setq coords (list 
(list 4159.4375 -167.717) 
(list 4085.415 -167.267) 
(list 4085.415 -167.444) 
(list 4159.4375 -167.794)))
(apply 'command (append '("pline") coords '("c")))
(setq currobj (ssadd (entlast) currobj))
(setq coords (list 
(list 4159.4375 -167.937) 
(list 4085.415 -167.587) 
(list 4085.415 -167.764) 
(list 4159.4375 -168.014)))
(apply 'command (append '("pline") coords '("c")))
(setq currobj (ssadd (entlast) currobj))
(setq coords (list 
(list 4159.4375 -168.157) 
(list 4085.415 -167.907) 
(list 4085.415 -168.084) 
(list 4159.4375 -168.234)))
(apply 'command (append '("pline") coords '("c")))
(setq currobj (ssadd (entlast) currobj))
(setq coords (list 
(list 4159.4375 -168.377) 
(list 4085.415 -168.227) 
(list 4085.415 -168.404) 
(list 4159.4375 -168.454)))
(apply 'command (append '("pline") coords '("c")))
(setq currobj (ssadd (entlast) currobj))
(setq coords (list 
(list 4159.4375 -168.597) 
(list 4085.415 -168.547) 
(list 4085.415 -168.724) 
(list 4159.4375 -168.674)))
(apply 'command (append '("pline") coords '("c")))
(setq currobj (ssadd (entlast) currobj))
(setq coords (list 
(list 4159.4375 -168.817) 
(list 4085.415 -168.867) 
(list 4085.415 -169.044) 
(list 4159.4375 -168.894)))
(apply 'command (append '("pline") coords '("c")))
(setq currobj (ssadd (entlast) currobj))
(setq coords (list 
(list 4159.4375 -169.037) 
(list 4085.415 -169.187) 
(list 4085.415 -169.364) 
(list 4159.4375 -169.114)))
(apply 'command (append '("pline") coords '("c")))
(setq currobj (ssadd (entlast) currobj))
(setq coords (list 
(list 4159.4375 -169.257) 
(list 4085.415 -169.507) 
(list 4085.415 -169.684) 
(list 4159.4375 -169.334)))
(apply 'command (append '("pline") coords '("c")))
(setq currobj (ssadd (entlast) currobj))
(setq coords (list 
(list 4159.4375 -169.477) 
(list 4085.415 -169.827) 
(list 4085.415 -170.004) 
(list 4159.4375 -169.554)))
(apply 'command (append '("pline") coords '("c")))
(setq currobj (ssadd (entlast) currobj))
(setq coords (list 
(list 4159.4375 -169.697) 
(list 4085.415 -170.147) 
(list 4085.415 -170.324) 
(list 4159.4375 -169.774)))
(apply 'command (append '("pline") coords '("c")))
(setq currobj (ssadd (entlast) currobj))
(setq coords (list 
(list 4159.4375 -169.917) 
(list 4085.415 -170.467) 
(list 4085.415 -170.644) 
(list 4159.4375 -169.994)))
(apply 'command (append '("pline") coords '("c")))
(setq currobj (ssadd (entlast) currobj))
(setq coords (list 
(list 4159.4375 -170.137) 
(list 4085.415 -170.787) 
(list 4085.415 -170.964) 
(list 4159.4375 -170.214)))
(apply 'command (append '("pline") coords '("c")))
(setq currobj (ssadd (entlast) currobj))
(command "_layer" "set" "nitride" "")
(command "_layer" "set" "text" "")
(command "_circle" "4159.0625,-181.357" "0.075")
(command "_circle" "4159.0625,-181.057" "0.075")
(command "_circle" "4159.0625,-180.757" "0.075")
(command "_circle" "4159.0625,-180.457" "0.075")
(command "_circle" "4159.0625,-180.157" "0.075")
(command "_circle" "4158.7625,-181.357" "0.075")
(command "_circle" "4158.7625,-181.057" "0.075")
(command "_circle" "4158.7625,-180.757" "0.075")
(command "_circle" "4158.7625,-180.457" "0.075")
(command "_circle" "4158.7625,-180.157" "0.075")
(command "_circle" "4158.4625,-181.357" "0.075")
(command "_circle" "4158.4625,-181.057" "0.075")
(command "_circle" "4158.4625,-180.757" "0.075")
(command "_circle" "4158.4625,-180.457" "0.075")
(command "_circle" "4158.4625,-180.157" "0.075")
(command "_circle" "4158.1625,-181.357" "0.075")
(command "_circle" "4158.1625,-181.057" "0.075")
(command "_circle" "4158.1625,-180.757" "0.075")
(command "_circle" "4158.1625,-180.457" "0.075")
(command "_circle" "4158.1625,-180.157" "0.075")
(command "_circle" "4157.8625,-181.357" "0.075")
(command "_circle" "4157.8625,-181.057" "0.075")
(command "_circle" "4157.8625,-180.757" "0.075")
(command "_circle" "4157.8625,-180.457" "0.075")
(command "_circle" "4157.8625,-180.157" "0.075")
(command "_layer" "set" "nitride" "")
(setq coords (list 
(list 4160.2625 -155.914) 
(list 4160.2625 -40.2693) 
(list 4159.7375 -40.2693) 
(list 4159.7375 -155.914)))
(apply 'command (append '("pline") coords '("c")))
(setq currobj (ssadd (entlast) currobj))
(command "_layer" "set" "prebias" "")
(command "_rectangle" "4159.7375,-155.914" "4160.2625,-40.2693")
(setq currobj (ssadd (entlast) currobj))
(command "_layer" "set" "nitride" "")
(setq coords (list 
(list 4160.2625 -40.2693) 
(list 4160.5625 -30.2693) 
(list 4160.5625 -30.2693) 
(list 4160.5625 -29.2693) 
(list 4234.585 -30.0193) 
(list 4234.585 -25.0763) 
(list 4160.5625 -25.8263) 
(list 4160.5625 -24.8263) 
(list 4160.5625 -24.8263) 
(list 4160.2625 -14.8263) 
(list 4159.7375 -14.8263) 
(list 4159.4375 -24.8263) 
(list 4159.4375 -24.8263) 
(list 4159.4375 -25.8263) 
(list 4085.415 -25.0763) 
(list 4085.415 -30.0193) 
(list 4159.4375 -29.2693) 
(list 4159.4375 -30.2693) 
(list 4159.4375 -30.2693) 
(list 4159.7375 -40.2693)))
(apply 'command (append '("pline") coords '("c")))
(setq currobj (ssadd (entlast) currobj))
(command "_layer" "set" "prebias" "")
(setq coords (list 
(list 4159.4375 -40.2693) 
(list 4159.4375 -29.2693) 
(list 4085.415 -30.0193) 
(list 4085.415 -25.0763) 
(list 4159.4375 -25.8263) 
(list 4159.4375 -14.8263) 
(list 4160.5625 -14.8263) 
(list 4160.5625 -25.8263) 
(list 4234.585 -25.0763) 
(list 4234.585 -30.0193) 
(list 4160.5625 -29.2693) 
(list 4160.5625 -40.2693)))
(apply 'command (append '("pline") coords '("c")))
(setq currobj (ssadd (entlast) currobj))
(command "_layer" "set" "nitride" "")
(command "_layer" "set" "fda1" "")
(setq coords (list 
(list 4160.5625 -29.1263) 
(list 4234.585 -29.8763) 
(list 4234.585 -29.6993) 
(list 4160.5625 -29.0493)))
(apply 'command (append '("pline") coords '("c")))
(setq currobj (ssadd (entlast) currobj))
(setq coords (list 
(list 4160.5625 -28.9063) 
(list 4234.585 -29.5563) 
(list 4234.585 -29.3793) 
(list 4160.5625 -28.8293)))
(apply 'command (append '("pline") coords '("c")))
(setq currobj (ssadd (entlast) currobj))
(setq coords (list 
(list 4160.5625 -28.6863) 
(list 4234.585 -29.2363) 
(list 4234.585 -29.0593) 
(list 4160.5625 -28.6093)))
(apply 'command (append '("pline") coords '("c")))
(setq currobj (ssadd (entlast) currobj))
(setq coords (list 
(list 4160.5625 -28.4663) 
(list 4234.585 -28.9163) 
(list 4234.585 -28.7393) 
(list 4160.5625 -28.3893)))
(apply 'command (append '("pline") coords '("c")))
(setq currobj (ssadd (entlast) currobj))
(setq coords (list 
(list 4160.5625 -28.2463) 
(list 4234.585 -28.5963) 
(list 4234.585 -28.4193) 
(list 4160.5625 -28.1693)))
(apply 'command (append '("pline") coords '("c")))
(setq currobj (ssadd (entlast) currobj))
(setq coords (list 
(list 4160.5625 -28.0263) 
(list 4234.585 -28.2763) 
(list 4234.585 -28.0993) 
(list 4160.5625 -27.9493)))
(apply 'command (append '("pline") coords '("c")))
(setq currobj (ssadd (entlast) currobj))
(setq coords (list 
(list 4160.5625 -27.8063) 
(list 4234.585 -27.9563) 
(list 4234.585 -27.7793) 
(list 4160.5625 -27.7293)))
(apply 'command (append '("pline") coords '("c")))
(setq currobj (ssadd (entlast) currobj))
(setq coords (list 
(list 4160.5625 -27.5863) 
(list 4234.585 -27.6363) 
(list 4234.585 -27.4593) 
(list 4160.5625 -27.5093)))
(apply 'command (append '("pline") coords '("c")))
(setq currobj (ssadd (entlast) currobj))
(setq coords (list 
(list 4160.5625 -27.3663) 
(list 4234.585 -27.3163) 
(list 4234.585 -27.1393) 
(list 4160.5625 -27.2893)))
(apply 'command (append '("pline") coords '("c")))
(setq currobj (ssadd (entlast) currobj))
(setq coords (list 
(list 4160.5625 -27.1463) 
(list 4234.585 -26.9963) 
(list 4234.585 -26.8193) 
(list 4160.5625 -27.0693)))
(apply 'command (append '("pline") coords '("c")))
(setq currobj (ssadd (entlast) currobj))
(setq coords (list 
(list 4160.5625 -26.9263) 
(list 4234.585 -26.6763) 
(list 4234.585 -26.4993) 
(list 4160.5625 -26.8493)))
(apply 'command (append '("pline") coords '("c")))
(setq currobj (ssadd (entlast) currobj))
(setq coords (list 
(list 4160.5625 -26.7063) 
(list 4234.585 -26.3563) 
(list 4234.585 -26.1793) 
(list 4160.5625 -26.6293)))
(apply 'command (append '("pline") coords '("c")))
(setq currobj (ssadd (entlast) currobj))
(setq coords (list 
(list 4160.5625 -26.4863) 
(list 4234.585 -26.0363) 
(list 4234.585 -25.8593) 
(list 4160.5625 -26.4093)))
(apply 'command (append '("pline") coords '("c")))
(setq currobj (ssadd (entlast) currobj))
(setq coords (list 
(list 4160.5625 -26.2663) 
(list 4234.585 -25.7163) 
(list 4234.585 -25.5393) 
(list 4160.5625 -26.1893)))
(apply 'command (append '("pline") coords '("c")))
(setq currobj (ssadd (entlast) currobj))
(setq coords (list 
(list 4160.5625 -26.0463) 
(list 4234.585 -25.3963) 
(list 4234.585 -25.2193) 
(list 4160.5625 -25.9693)))
(apply 'command (append '("pline") coords '("c")))
(setq currobj (ssadd (entlast) currobj))
(setq coords (list 
(list 4159.4375 -25.9693) 
(list 4085.415 -25.2193) 
(list 4085.415 -25.3963) 
(list 4159.4375 -26.0463)))
(apply 'command (append '("pline") coords '("c")))
(setq currobj (ssadd (entlast) currobj))
(setq coords (list 
(list 4159.4375 -26.1893) 
(list 4085.415 -25.5393) 
(list 4085.415 -25.7163) 
(list 4159.4375 -26.2663)))
(apply 'command (append '("pline") coords '("c")))
(setq currobj (ssadd (entlast) currobj))
(setq coords (list 
(list 4159.4375 -26.4093) 
(list 4085.415 -25.8593) 
(list 4085.415 -26.0363) 
(list 4159.4375 -26.4863)))
(apply 'command (append '("pline") coords '("c")))
(setq currobj (ssadd (entlast) currobj))
(setq coords (list 
(list 4159.4375 -26.6293) 
(list 4085.415 -26.1793) 
(list 4085.415 -26.3563) 
(list 4159.4375 -26.7063)))
(apply 'command (append '("pline") coords '("c")))
(setq currobj (ssadd (entlast) currobj))
(setq coords (list 
(list 4159.4375 -26.8493) 
(list 4085.415 -26.4993) 
(list 4085.415 -26.6763) 
(list 4159.4375 -26.9263)))
(apply 'command (append '("pline") coords '("c")))
(setq currobj (ssadd (entlast) currobj))
(setq coords (list 
(list 4159.4375 -27.0693) 
(list 4085.415 -26.8193) 
(list 4085.415 -26.9963) 
(list 4159.4375 -27.1463)))
(apply 'command (append '("pline") coords '("c")))
(setq currobj (ssadd (entlast) currobj))
(setq coords (list 
(list 4159.4375 -27.2893) 
(list 4085.415 -27.1393) 
(list 4085.415 -27.3163) 
(list 4159.4375 -27.3663)))
(apply 'command (append '("pline") coords '("c")))
(setq currobj (ssadd (entlast) currobj))
(setq coords (list 
(list 4159.4375 -27.5093) 
(list 4085.415 -27.4593) 
(list 4085.415 -27.6363) 
(list 4159.4375 -27.5863)))
(apply 'command (append '("pline") coords '("c")))
(setq currobj (ssadd (entlast) currobj))
(setq coords (list 
(list 4159.4375 -27.7293) 
(list 4085.415 -27.7793) 
(list 4085.415 -27.9563) 
(list 4159.4375 -27.8063)))
(apply 'command (append '("pline") coords '("c")))
(setq currobj (ssadd (entlast) currobj))
(setq coords (list 
(list 4159.4375 -27.9493) 
(list 4085.415 -28.0993) 
(list 4085.415 -28.2763) 
(list 4159.4375 -28.0263)))
(apply 'command (append '("pline") coords '("c")))
(setq currobj (ssadd (entlast) currobj))
(setq coords (list 
(list 4159.4375 -28.1693) 
(list 4085.415 -28.4193) 
(list 4085.415 -28.5963) 
(list 4159.4375 -28.2463)))
(apply 'command (append '("pline") coords '("c")))
(setq currobj (ssadd (entlast) currobj))
(setq coords (list 
(list 4159.4375 -28.3893) 
(list 4085.415 -28.7393) 
(list 4085.415 -28.9163) 
(list 4159.4375 -28.4663)))
(apply 'command (append '("pline") coords '("c")))
(setq currobj (ssadd (entlast) currobj))
(setq coords (list 
(list 4159.4375 -28.6093) 
(list 4085.415 -29.0593) 
(list 4085.415 -29.2363) 
(list 4159.4375 -28.6863)))
(apply 'command (append '("pline") coords '("c")))
(setq currobj (ssadd (entlast) currobj))
(setq coords (list 
(list 4159.4375 -28.8293) 
(list 4085.415 -29.3793) 
(list 4085.415 -29.5563) 
(list 4159.4375 -28.9063)))
(apply 'command (append '("pline") coords '("c")))
(setq currobj (ssadd (entlast) currobj))
(setq coords (list 
(list 4159.4375 -29.0493) 
(list 4085.415 -29.6993) 
(list 4085.415 -29.8763) 
(list 4159.4375 -29.1263)))
(apply 'command (append '("pline") coords '("c")))
(setq currobj (ssadd (entlast) currobj))
(command "_layer" "set" "nitride" "")
(command "_layer" "set" "text" "")
(command "_circle" "4159.0625,-40.2693" "0.075")
(command "_circle" "4159.0625,-39.9693" "0.075")
(command "_circle" "4159.0625,-39.6693" "0.075")
(command "_circle" "4159.0625,-39.3693" "0.075")
(command "_circle" "4159.0625,-39.0693" "0.075")
(command "_circle" "4158.7625,-40.2693" "0.075")
(command "_circle" "4158.7625,-39.9693" "0.075")
(command "_circle" "4158.7625,-39.6693" "0.075")
(command "_circle" "4158.7625,-39.3693" "0.075")
(command "_circle" "4158.7625,-39.0693" "0.075")
(command "_circle" "4158.4625,-40.2693" "0.075")
(command "_circle" "4158.4625,-39.9693" "0.075")
(command "_circle" "4158.4625,-39.6693" "0.075")
(command "_circle" "4158.4625,-39.3693" "0.075")
(command "_circle" "4158.4625,-39.0693" "0.075")
(command "_circle" "4158.1625,-40.2693" "0.075")
(command "_circle" "4158.1625,-39.9693" "0.075")
(command "_circle" "4158.1625,-39.6693" "0.075")
(command "_circle" "4158.1625,-39.3693" "0.075")
(command "_circle" "4158.1625,-39.0693" "0.075")
(command "_circle" "4157.8625,-40.2693" "0.075")
(command "_circle" "4157.8625,-39.9693" "0.075")
(command "_circle" "4157.8625,-39.6693" "0.075")
(command "_circle" "4157.8625,-39.3693" "0.075")
(command "_circle" "4157.8625,-39.0693" "0.075")
(command "_layer" "set" "nitride" "")
(setq coords (list 
(list 4160.2625 -14.8263) 
(list 4160.2625 100.8184) 
(list 4159.7375 100.8184) 
(list 4159.7375 -14.8263)))
(apply 'command (append '("pline") coords '("c")))
(setq currobj (ssadd (entlast) currobj))
(command "_layer" "set" "prebias" "")
(command "_rectangle" "4159.7375,-14.8263" "4160.2625,100.8184")
(setq currobj (ssadd (entlast) currobj))
(command "_layer" "set" "nitride" "")
(setq coords (list 
(list 4160.2625 100.8184) 
(list 4160.5625 110.8184) 
(list 4160.5625 110.8184) 
(list 4160.5625 111.8184) 
(list 4234.585 111.0684) 
(list 4234.585 116.0114) 
(list 4160.5625 115.2614) 
(list 4160.5625 116.2614) 
(list 4160.5625 116.2614) 
(list 4160.2625 126.2614) 
(list 4159.7375 126.2614) 
(list 4159.4375 116.2614) 
(list 4159.4375 116.2614) 
(list 4159.4375 115.2614) 
(list 4085.415 116.0114) 
(list 4085.415 111.0684) 
(list 4159.4375 111.8184) 
(list 4159.4375 110.8184) 
(list 4159.4375 110.8184) 
(list 4159.7375 100.8184)))
(apply 'command (append '("pline") coords '("c")))
(setq currobj (ssadd (entlast) currobj))
(command "_layer" "set" "prebias" "")
(setq coords (list 
(list 4159.4375 100.8184) 
(list 4159.4375 111.8184) 
(list 4085.415 111.0684) 
(list 4085.415 116.0114) 
(list 4159.4375 115.2614) 
(list 4159.4375 126.2614) 
(list 4160.5625 126.2614) 
(list 4160.5625 115.2614) 
(list 4234.585 116.0114) 
(list 4234.585 111.0684) 
(list 4160.5625 111.8184) 
(list 4160.5625 100.8184)))
(apply 'command (append '("pline") coords '("c")))
(setq currobj (ssadd (entlast) currobj))
(command "_layer" "set" "nitride" "")
(command "_layer" "set" "fda1" "")
(setq coords (list 
(list 4160.5625 111.9614) 
(list 4234.585 111.2114) 
(list 4234.585 111.3884) 
(list 4160.5625 112.0384)))
(apply 'command (append '("pline") coords '("c")))
(setq currobj (ssadd (entlast) currobj))
(setq coords (list 
(list 4160.5625 112.1814) 
(list 4234.585 111.5314) 
(list 4234.585 111.7084) 
(list 4160.5625 112.2584)))
(apply 'command (append '("pline") coords '("c")))
(setq currobj (ssadd (entlast) currobj))
(setq coords (list 
(list 4160.5625 112.4014) 
(list 4234.585 111.8514) 
(list 4234.585 112.0284) 
(list 4160.5625 112.4784)))
(apply 'command (append '("pline") coords '("c")))
(setq currobj (ssadd (entlast) currobj))
(setq coords (list 
(list 4160.5625 112.6214) 
(list 4234.585 112.1714) 
(list 4234.585 112.3484) 
(list 4160.5625 112.6984)))
(apply 'command (append '("pline") coords '("c")))
(setq currobj (ssadd (entlast) currobj))
(setq coords (list 
(list 4160.5625 112.8414) 
(list 4234.585 112.4914) 
(list 4234.585 112.6684) 
(list 4160.5625 112.9184)))
(apply 'command (append '("pline") coords '("c")))
(setq currobj (ssadd (entlast) currobj))
(setq coords (list 
(list 4160.5625 113.0614) 
(list 4234.585 112.8114) 
(list 4234.585 112.9884) 
(list 4160.5625 113.1384)))
(apply 'command (append '("pline") coords '("c")))
(setq currobj (ssadd (entlast) currobj))
(setq coords (list 
(list 4160.5625 113.2814) 
(list 4234.585 113.1314) 
(list 4234.585 113.3084) 
(list 4160.5625 113.3584)))
(apply 'command (append '("pline") coords '("c")))
(setq currobj (ssadd (entlast) currobj))
(setq coords (list 
(list 4160.5625 113.5014) 
(list 4234.585 113.4514) 
(list 4234.585 113.6284) 
(list 4160.5625 113.5784)))
(apply 'command (append '("pline") coords '("c")))
(setq currobj (ssadd (entlast) currobj))
(setq coords (list 
(list 4160.5625 113.7214) 
(list 4234.585 113.7714) 
(list 4234.585 113.9484) 
(list 4160.5625 113.7984)))
(apply 'command (append '("pline") coords '("c")))
(setq currobj (ssadd (entlast) currobj))
(setq coords (list 
(list 4160.5625 113.9414) 
(list 4234.585 114.0914) 
(list 4234.585 114.2684) 
(list 4160.5625 114.0184)))
(apply 'command (append '("pline") coords '("c")))
(setq currobj (ssadd (entlast) currobj))
(setq coords (list 
(list 4160.5625 114.1614) 
(list 4234.585 114.4114) 
(list 4234.585 114.5884) 
(list 4160.5625 114.2384)))
(apply 'command (append '("pline") coords '("c")))
(setq currobj (ssadd (entlast) currobj))
(setq coords (list 
(list 4160.5625 114.3814) 
(list 4234.585 114.7314) 
(list 4234.585 114.9084) 
(list 4160.5625 114.4584)))
(apply 'command (append '("pline") coords '("c")))
(setq currobj (ssadd (entlast) currobj))
(setq coords (list 
(list 4160.5625 114.6014) 
(list 4234.585 115.0514) 
(list 4234.585 115.2284) 
(list 4160.5625 114.6784)))
(apply 'command (append '("pline") coords '("c")))
(setq currobj (ssadd (entlast) currobj))
(setq coords (list 
(list 4160.5625 114.8214) 
(list 4234.585 115.3714) 
(list 4234.585 115.5484) 
(list 4160.5625 114.8984)))
(apply 'command (append '("pline") coords '("c")))
(setq currobj (ssadd (entlast) currobj))
(setq coords (list 
(list 4160.5625 115.0414) 
(list 4234.585 115.6914) 
(list 4234.585 115.8684) 
(list 4160.5625 115.1184)))
(apply 'command (append '("pline") coords '("c")))
(setq currobj (ssadd (entlast) currobj))
(setq coords (list 
(list 4159.4375 115.1184) 
(list 4085.415 115.8684) 
(list 4085.415 115.6914) 
(list 4159.4375 115.0414)))
(apply 'command (append '("pline") coords '("c")))
(setq currobj (ssadd (entlast) currobj))
(setq coords (list 
(list 4159.4375 114.8984) 
(list 4085.415 115.5484) 
(list 4085.415 115.3714) 
(list 4159.4375 114.8214)))
(apply 'command (append '("pline") coords '("c")))
(setq currobj (ssadd (entlast) currobj))
(setq coords (list 
(list 4159.4375 114.6784) 
(list 4085.415 115.2284) 
(list 4085.415 115.0514) 
(list 4159.4375 114.6014)))
(apply 'command (append '("pline") coords '("c")))
(setq currobj (ssadd (entlast) currobj))
(setq coords (list 
(list 4159.4375 114.4584) 
(list 4085.415 114.9084) 
(list 4085.415 114.7314) 
(list 4159.4375 114.3814)))
(apply 'command (append '("pline") coords '("c")))
(setq currobj (ssadd (entlast) currobj))
(setq coords (list 
(list 4159.4375 114.2384) 
(list 4085.415 114.5884) 
(list 4085.415 114.4114) 
(list 4159.4375 114.1614)))
(apply 'command (append '("pline") coords '("c")))
(setq currobj (ssadd (entlast) currobj))
(setq coords (list 
(list 4159.4375 114.0184) 
(list 4085.415 114.2684) 
(list 4085.415 114.0914) 
(list 4159.4375 113.9414)))
(apply 'command (append '("pline") coords '("c")))
(setq currobj (ssadd (entlast) currobj))
(setq coords (list 
(list 4159.4375 113.7984) 
(list 4085.415 113.9484) 
(list 4085.415 113.7714) 
(list 4159.4375 113.7214)))
(apply 'command (append '("pline") coords '("c")))
(setq currobj (ssadd (entlast) currobj))
(setq coords (list 
(list 4159.4375 113.5784) 
(list 4085.415 113.6284) 
(list 4085.415 113.4514) 
(list 4159.4375 113.5014)))
(apply 'command (append '("pline") coords '("c")))
(setq currobj (ssadd (entlast) currobj))
(setq coords (list 
(list 4159.4375 113.3584) 
(list 4085.415 113.3084) 
(list 4085.415 113.1314) 
(list 4159.4375 113.2814)))
(apply 'command (append '("pline") coords '("c")))
(setq currobj (ssadd (entlast) currobj))
(setq coords (list 
(list 4159.4375 113.1384) 
(list 4085.415 112.9884) 
(list 4085.415 112.8114) 
(list 4159.4375 113.0614)))
(apply 'command (append '("pline") coords '("c")))
(setq currobj (ssadd (entlast) currobj))
(setq coords (list 
(list 4159.4375 112.9184) 
(list 4085.415 112.6684) 
(list 4085.415 112.4914) 
(list 4159.4375 112.8414)))
(apply 'command (append '("pline") coords '("c")))
(setq currobj (ssadd (entlast) currobj))
(setq coords (list 
(list 4159.4375 112.6984) 
(list 4085.415 112.3484) 
(list 4085.415 112.1714) 
(list 4159.4375 112.6214)))
(apply 'command (append '("pline") coords '("c")))
(setq currobj (ssadd (entlast) currobj))
(setq coords (list 
(list 4159.4375 112.4784) 
(list 4085.415 112.0284) 
(list 4085.415 111.8514) 
(list 4159.4375 112.4014)))
(apply 'command (append '("pline") coords '("c")))
(setq currobj (ssadd (entlast) currobj))
(setq coords (list 
(list 4159.4375 112.2584) 
(list 4085.415 111.7084) 
(list 4085.415 111.5314) 
(list 4159.4375 112.1814)))
(apply 'command (append '("pline") coords '("c")))
(setq currobj (ssadd (entlast) currobj))
(setq coords (list 
(list 4159.4375 112.0384) 
(list 4085.415 111.3884) 
(list 4085.415 111.2114) 
(list 4159.4375 111.9614)))
(apply 'command (append '("pline") coords '("c")))
(setq currobj (ssadd (entlast) currobj))
(command "_layer" "set" "nitride" "")
(command "_layer" "set" "text" "")
(command "_circle" "4159.0625,100.8184" "0.075")
(command "_circle" "4159.0625,101.1184" "0.075")
(command "_circle" "4159.0625,101.4184" "0.075")
(command "_circle" "4159.0625,101.7184" "0.075")
(command "_circle" "4159.0625,102.0184" "0.075")
(command "_circle" "4158.7625,100.8184" "0.075")
(command "_circle" "4158.7625,101.1184" "0.075")
(command "_circle" "4158.7625,101.4184" "0.075")
(command "_circle" "4158.7625,101.7184" "0.075")
(command "_circle" "4158.7625,102.0184" "0.075")
(command "_circle" "4158.4625,100.8184" "0.075")
(command "_circle" "4158.4625,101.1184" "0.075")
(command "_circle" "4158.4625,101.4184" "0.075")
(command "_circle" "4158.4625,101.7184" "0.075")
(command "_circle" "4158.4625,102.0184" "0.075")
(command "_circle" "4158.1625,100.8184" "0.075")
(command "_circle" "4158.1625,101.1184" "0.075")
(command "_circle" "4158.1625,101.4184" "0.075")
(command "_circle" "4158.1625,101.7184" "0.075")
(command "_circle" "4158.1625,102.0184" "0.075")
(command "_circle" "4157.8625,100.8184" "0.075")
(command "_circle" "4157.8625,101.1184" "0.075")
(command "_circle" "4157.8625,101.4184" "0.075")
(command "_circle" "4157.8625,101.7184" "0.075")
(command "_circle" "4157.8625,102.0184" "0.075")
(command "_layer" "set" "nitride" "")
(setq coords (list 
(list 4160.2625 126.2614) 
(list 4160.2625 241.9061) 
(list 4159.7375 241.9061) 
(list 4159.7375 126.2614)))
(apply 'command (append '("pline") coords '("c")))
(setq currobj (ssadd (entlast) currobj))
(command "_layer" "set" "prebias" "")
(command "_rectangle" "4159.7375,126.2614" "4160.2625,241.9061")
(setq currobj (ssadd (entlast) currobj))
(command "_layer" "set" "nitride" "")
(setq coords (list 
(list 4160.2625 241.9061) 
(list 4160.5625 251.9061) 
(list 4160.5625 251.9061) 
(list 4160.5625 252.9061) 
(list 4234.585 252.1561) 
(list 4234.585 257.0991) 
(list 4160.5625 256.3491) 
(list 4160.5625 257.3491) 
(list 4160.5625 257.3491) 
(list 4160.2625 267.3491) 
(list 4159.7375 267.3491) 
(list 4159.4375 257.3491) 
(list 4159.4375 257.3491) 
(list 4159.4375 256.3491) 
(list 4085.415 257.0991) 
(list 4085.415 252.1561) 
(list 4159.4375 252.9061) 
(list 4159.4375 251.9061) 
(list 4159.4375 251.9061) 
(list 4159.7375 241.9061)))
(apply 'command (append '("pline") coords '("c")))
(setq currobj (ssadd (entlast) currobj))
(command "_layer" "set" "prebias" "")
(setq coords (list 
(list 4159.4375 241.9061) 
(list 4159.4375 252.9061) 
(list 4085.415 252.1561) 
(list 4085.415 257.0991) 
(list 4159.4375 256.3491) 
(list 4159.4375 267.3491) 
(list 4160.5625 267.3491) 
(list 4160.5625 256.3491) 
(list 4234.585 257.0991) 
(list 4234.585 252.1561) 
(list 4160.5625 252.9061) 
(list 4160.5625 241.9061)))
(apply 'command (append '("pline") coords '("c")))
(setq currobj (ssadd (entlast) currobj))
(command "_layer" "set" "nitride" "")
(command "_layer" "set" "fda1" "")
(setq coords (list 
(list 4160.5625 253.0491) 
(list 4234.585 252.2991) 
(list 4234.585 252.4761) 
(list 4160.5625 253.1261)))
(apply 'command (append '("pline") coords '("c")))
(setq currobj (ssadd (entlast) currobj))
(setq coords (list 
(list 4160.5625 253.2691) 
(list 4234.585 252.6191) 
(list 4234.585 252.7961) 
(list 4160.5625 253.3461)))
(apply 'command (append '("pline") coords '("c")))
(setq currobj (ssadd (entlast) currobj))
(setq coords (list 
(list 4160.5625 253.4891) 
(list 4234.585 252.9391) 
(list 4234.585 253.1161) 
(list 4160.5625 253.5661)))
(apply 'command (append '("pline") coords '("c")))
(setq currobj (ssadd (entlast) currobj))
(setq coords (list 
(list 4160.5625 253.7091) 
(list 4234.585 253.2591) 
(list 4234.585 253.4361) 
(list 4160.5625 253.7861)))
(apply 'command (append '("pline") coords '("c")))
(setq currobj (ssadd (entlast) currobj))
(setq coords (list 
(list 4160.5625 253.9291) 
(list 4234.585 253.5791) 
(list 4234.585 253.7561) 
(list 4160.5625 254.0061)))
(apply 'command (append '("pline") coords '("c")))
(setq currobj (ssadd (entlast) currobj))
(setq coords (list 
(list 4160.5625 254.1491) 
(list 4234.585 253.8991) 
(list 4234.585 254.0761) 
(list 4160.5625 254.2261)))
(apply 'command (append '("pline") coords '("c")))
(setq currobj (ssadd (entlast) currobj))
(setq coords (list 
(list 4160.5625 254.3691) 
(list 4234.585 254.2191) 
(list 4234.585 254.3961) 
(list 4160.5625 254.4461)))
(apply 'command (append '("pline") coords '("c")))
(setq currobj (ssadd (entlast) currobj))
(setq coords (list 
(list 4160.5625 254.5891) 
(list 4234.585 254.5391) 
(list 4234.585 254.7161) 
(list 4160.5625 254.6661)))
(apply 'command (append '("pline") coords '("c")))
(setq currobj (ssadd (entlast) currobj))
(setq coords (list 
(list 4160.5625 254.8091) 
(list 4234.585 254.8591) 
(list 4234.585 255.0361) 
(list 4160.5625 254.8861)))
(apply 'command (append '("pline") coords '("c")))
(setq currobj (ssadd (entlast) currobj))
(setq coords (list 
(list 4160.5625 255.0291) 
(list 4234.585 255.1791) 
(list 4234.585 255.3561) 
(list 4160.5625 255.1061)))
(apply 'command (append '("pline") coords '("c")))
(setq currobj (ssadd (entlast) currobj))
(setq coords (list 
(list 4160.5625 255.2491) 
(list 4234.585 255.4991) 
(list 4234.585 255.6761) 
(list 4160.5625 255.3261)))
(apply 'command (append '("pline") coords '("c")))
(setq currobj (ssadd (entlast) currobj))
(setq coords (list 
(list 4160.5625 255.4691) 
(list 4234.585 255.8191) 
(list 4234.585 255.9961) 
(list 4160.5625 255.5461)))
(apply 'command (append '("pline") coords '("c")))
(setq currobj (ssadd (entlast) currobj))
(setq coords (list 
(list 4160.5625 255.6891) 
(list 4234.585 256.1391) 
(list 4234.585 256.3161) 
(list 4160.5625 255.7661)))
(apply 'command (append '("pline") coords '("c")))
(setq currobj (ssadd (entlast) currobj))
(setq coords (list 
(list 4160.5625 255.9091) 
(list 4234.585 256.4591) 
(list 4234.585 256.6361) 
(list 4160.5625 255.9861)))
(apply 'command (append '("pline") coords '("c")))
(setq currobj (ssadd (entlast) currobj))
(setq coords (list 
(list 4160.5625 256.1291) 
(list 4234.585 256.7791) 
(list 4234.585 256.9561) 
(list 4160.5625 256.2061)))
(apply 'command (append '("pline") coords '("c")))
(setq currobj (ssadd (entlast) currobj))
(setq coords (list 
(list 4159.4375 256.2061) 
(list 4085.415 256.9561) 
(list 4085.415 256.7791) 
(list 4159.4375 256.1291)))
(apply 'command (append '("pline") coords '("c")))
(setq currobj (ssadd (entlast) currobj))
(setq coords (list 
(list 4159.4375 255.9861) 
(list 4085.415 256.6361) 
(list 4085.415 256.4591) 
(list 4159.4375 255.9091)))
(apply 'command (append '("pline") coords '("c")))
(setq currobj (ssadd (entlast) currobj))
(setq coords (list 
(list 4159.4375 255.7661) 
(list 4085.415 256.3161) 
(list 4085.415 256.1391) 
(list 4159.4375 255.6891)))
(apply 'command (append '("pline") coords '("c")))
(setq currobj (ssadd (entlast) currobj))
(setq coords (list 
(list 4159.4375 255.5461) 
(list 4085.415 255.9961) 
(list 4085.415 255.8191) 
(list 4159.4375 255.4691)))
(apply 'command (append '("pline") coords '("c")))
(setq currobj (ssadd (entlast) currobj))
(setq coords (list 
(list 4159.4375 255.3261) 
(list 4085.415 255.6761) 
(list 4085.415 255.4991) 
(list 4159.4375 255.2491)))
(apply 'command (append '("pline") coords '("c")))
(setq currobj (ssadd (entlast) currobj))
(setq coords (list 
(list 4159.4375 255.1061) 
(list 4085.415 255.3561) 
(list 4085.415 255.1791) 
(list 4159.4375 255.0291)))
(apply 'command (append '("pline") coords '("c")))
(setq currobj (ssadd (entlast) currobj))
(setq coords (list 
(list 4159.4375 254.8861) 
(list 4085.415 255.0361) 
(list 4085.415 254.8591) 
(list 4159.4375 254.8091)))
(apply 'command (append '("pline") coords '("c")))
(setq currobj (ssadd (entlast) currobj))
(setq coords (list 
(list 4159.4375 254.6661) 
(list 4085.415 254.7161) 
(list 4085.415 254.5391) 
(list 4159.4375 254.5891)))
(apply 'command (append '("pline") coords '("c")))
(setq currobj (ssadd (entlast) currobj))
(setq coords (list 
(list 4159.4375 254.4461) 
(list 4085.415 254.3961) 
(list 4085.415 254.2191) 
(list 4159.4375 254.3691)))
(apply 'command (append '("pline") coords '("c")))
(setq currobj (ssadd (entlast) currobj))
(setq coords (list 
(list 4159.4375 254.2261) 
(list 4085.415 254.0761) 
(list 4085.415 253.8991) 
(list 4159.4375 254.1491)))
(apply 'command (append '("pline") coords '("c")))
(setq currobj (ssadd (entlast) currobj))
(setq coords (list 
(list 4159.4375 254.0061) 
(list 4085.415 253.7561) 
(list 4085.415 253.5791) 
(list 4159.4375 253.9291)))
(apply 'command (append '("pline") coords '("c")))
(setq currobj (ssadd (entlast) currobj))
(setq coords (list 
(list 4159.4375 253.7861) 
(list 4085.415 253.4361) 
(list 4085.415 253.2591) 
(list 4159.4375 253.7091)))
(apply 'command (append '("pline") coords '("c")))
(setq currobj (ssadd (entlast) currobj))
(setq coords (list 
(list 4159.4375 253.5661) 
(list 4085.415 253.1161) 
(list 4085.415 252.9391) 
(list 4159.4375 253.4891)))
(apply 'command (append '("pline") coords '("c")))
(setq currobj (ssadd (entlast) currobj))
(setq coords (list 
(list 4159.4375 253.3461) 
(list 4085.415 252.7961) 
(list 4085.415 252.6191) 
(list 4159.4375 253.2691)))
(apply 'command (append '("pline") coords '("c")))
(setq currobj (ssadd (entlast) currobj))
(setq coords (list 
(list 4159.4375 253.1261) 
(list 4085.415 252.4761) 
(list 4085.415 252.2991) 
(list 4159.4375 253.0491)))
(apply 'command (append '("pline") coords '("c")))
(setq currobj (ssadd (entlast) currobj))
(command "_layer" "set" "nitride" "")
(command "_layer" "set" "text" "")
(command "_circle" "4159.0625,241.9061" "0.075")
(command "_circle" "4159.0625,242.2061" "0.075")
(command "_circle" "4159.0625,242.5061" "0.075")
(command "_circle" "4159.0625,242.8061" "0.075")
(command "_circle" "4159.0625,243.1061" "0.075")
(command "_circle" "4158.7625,241.9061" "0.075")
(command "_circle" "4158.7625,242.2061" "0.075")
(command "_circle" "4158.7625,242.5061" "0.075")
(command "_circle" "4158.7625,242.8061" "0.075")
(command "_circle" "4158.7625,243.1061" "0.075")
(command "_circle" "4158.4625,241.9061" "0.075")
(command "_circle" "4158.4625,242.2061" "0.075")
(command "_circle" "4158.4625,242.5061" "0.075")
(command "_circle" "4158.4625,242.8061" "0.075")
(command "_circle" "4158.4625,243.1061" "0.075")
(command "_circle" "4158.1625,241.9061" "0.075")
(command "_circle" "4158.1625,242.2061" "0.075")
(command "_circle" "4158.1625,242.5061" "0.075")
(command "_circle" "4158.1625,242.8061" "0.075")
(command "_circle" "4158.1625,243.1061" "0.075")
(command "_circle" "4157.8625,241.9061" "0.075")
(command "_circle" "4157.8625,242.2061" "0.075")
(command "_circle" "4157.8625,242.5061" "0.075")
(command "_circle" "4157.8625,242.8061" "0.075")
(command "_circle" "4157.8625,243.1061" "0.075")
(command "_layer" "set" "nitride" "")
(setq coords (list 
(list 4160.2625 267.3491) 
(list 4160.2625 382.9939) 
(list 4159.7375 382.9939) 
(list 4159.7375 267.3491)))
(apply 'command (append '("pline") coords '("c")))
(setq currobj (ssadd (entlast) currobj))
(command "_layer" "set" "prebias" "")
(command "_rectangle" "4159.7375,267.3491" "4160.2625,382.9939")
(setq currobj (ssadd (entlast) currobj))
(command "_layer" "set" "nitride" "")
(setq coords (list 
(list 4160.2625 382.9939) 
(list 4160.5625 392.9939) 
(list 4160.5625 392.9939) 
(list 4160.5625 393.9939) 
(list 4234.585 393.2439) 
(list 4234.585 398.1869) 
(list 4160.5625 397.4369) 
(list 4160.5625 398.4369) 
(list 4160.5625 398.4369) 
(list 4160.2625 408.4369) 
(list 4159.7375 408.4369) 
(list 4159.4375 398.4369) 
(list 4159.4375 398.4369) 
(list 4159.4375 397.4369) 
(list 4085.415 398.1869) 
(list 4085.415 393.2439) 
(list 4159.4375 393.9939) 
(list 4159.4375 392.9939) 
(list 4159.4375 392.9939) 
(list 4159.7375 382.9939)))
(apply 'command (append '("pline") coords '("c")))
(setq currobj (ssadd (entlast) currobj))
(command "_layer" "set" "prebias" "")
(setq coords (list 
(list 4159.4375 382.9939) 
(list 4159.4375 393.9939) 
(list 4085.415 393.2439) 
(list 4085.415 398.1869) 
(list 4159.4375 397.4369) 
(list 4159.4375 408.4369) 
(list 4160.5625 408.4369) 
(list 4160.5625 397.4369) 
(list 4234.585 398.1869) 
(list 4234.585 393.2439) 
(list 4160.5625 393.9939) 
(list 4160.5625 382.9939)))
(apply 'command (append '("pline") coords '("c")))
(setq currobj (ssadd (entlast) currobj))
(command "_layer" "set" "nitride" "")
(command "_layer" "set" "fda1" "")
(setq coords (list 
(list 4160.5625 394.1369) 
(list 4234.585 393.3869) 
(list 4234.585 393.5639) 
(list 4160.5625 394.2139)))
(apply 'command (append '("pline") coords '("c")))
(setq currobj (ssadd (entlast) currobj))
(setq coords (list 
(list 4160.5625 394.3569) 
(list 4234.585 393.7069) 
(list 4234.585 393.8839) 
(list 4160.5625 394.4339)))
(apply 'command (append '("pline") coords '("c")))
(setq currobj (ssadd (entlast) currobj))
(setq coords (list 
(list 4160.5625 394.5769) 
(list 4234.585 394.0269) 
(list 4234.585 394.2039) 
(list 4160.5625 394.6539)))
(apply 'command (append '("pline") coords '("c")))
(setq currobj (ssadd (entlast) currobj))
(setq coords (list 
(list 4160.5625 394.7969) 
(list 4234.585 394.3469) 
(list 4234.585 394.5239) 
(list 4160.5625 394.8739)))
(apply 'command (append '("pline") coords '("c")))
(setq currobj (ssadd (entlast) currobj))
(setq coords (list 
(list 4160.5625 395.0169) 
(list 4234.585 394.6669) 
(list 4234.585 394.8439) 
(list 4160.5625 395.0939)))
(apply 'command (append '("pline") coords '("c")))
(setq currobj (ssadd (entlast) currobj))
(setq coords (list 
(list 4160.5625 395.2369) 
(list 4234.585 394.9869) 
(list 4234.585 395.1639) 
(list 4160.5625 395.3139)))
(apply 'command (append '("pline") coords '("c")))
(setq currobj (ssadd (entlast) currobj))
(setq coords (list 
(list 4160.5625 395.4569) 
(list 4234.585 395.3069) 
(list 4234.585 395.4839) 
(list 4160.5625 395.5339)))
(apply 'command (append '("pline") coords '("c")))
(setq currobj (ssadd (entlast) currobj))
(setq coords (list 
(list 4160.5625 395.6769) 
(list 4234.585 395.6269) 
(list 4234.585 395.8039) 
(list 4160.5625 395.7539)))
(apply 'command (append '("pline") coords '("c")))
(setq currobj (ssadd (entlast) currobj))
(setq coords (list 
(list 4160.5625 395.8969) 
(list 4234.585 395.9469) 
(list 4234.585 396.1239) 
(list 4160.5625 395.9739)))
(apply 'command (append '("pline") coords '("c")))
(setq currobj (ssadd (entlast) currobj))
(setq coords (list 
(list 4160.5625 396.1169) 
(list 4234.585 396.2669) 
(list 4234.585 396.4439) 
(list 4160.5625 396.1939)))
(apply 'command (append '("pline") coords '("c")))
(setq currobj (ssadd (entlast) currobj))
(setq coords (list 
(list 4160.5625 396.3369) 
(list 4234.585 396.5869) 
(list 4234.585 396.7639) 
(list 4160.5625 396.4139)))
(apply 'command (append '("pline") coords '("c")))
(setq currobj (ssadd (entlast) currobj))
(setq coords (list 
(list 4160.5625 396.5569) 
(list 4234.585 396.9069) 
(list 4234.585 397.0839) 
(list 4160.5625 396.6339)))
(apply 'command (append '("pline") coords '("c")))
(setq currobj (ssadd (entlast) currobj))
(setq coords (list 
(list 4160.5625 396.7769) 
(list 4234.585 397.2269) 
(list 4234.585 397.4039) 
(list 4160.5625 396.8539)))
(apply 'command (append '("pline") coords '("c")))
(setq currobj (ssadd (entlast) currobj))
(setq coords (list 
(list 4160.5625 396.9969) 
(list 4234.585 397.5469) 
(list 4234.585 397.7239) 
(list 4160.5625 397.0739)))
(apply 'command (append '("pline") coords '("c")))
(setq currobj (ssadd (entlast) currobj))
(setq coords (list 
(list 4160.5625 397.2169) 
(list 4234.585 397.8669) 
(list 4234.585 398.0439) 
(list 4160.5625 397.2939)))
(apply 'command (append '("pline") coords '("c")))
(setq currobj (ssadd (entlast) currobj))
(setq coords (list 
(list 4159.4375 397.2939) 
(list 4085.415 398.0439) 
(list 4085.415 397.8669) 
(list 4159.4375 397.2169)))
(apply 'command (append '("pline") coords '("c")))
(setq currobj (ssadd (entlast) currobj))
(setq coords (list 
(list 4159.4375 397.0739) 
(list 4085.415 397.7239) 
(list 4085.415 397.5469) 
(list 4159.4375 396.9969)))
(apply 'command (append '("pline") coords '("c")))
(setq currobj (ssadd (entlast) currobj))
(setq coords (list 
(list 4159.4375 396.8539) 
(list 4085.415 397.4039) 
(list 4085.415 397.2269) 
(list 4159.4375 396.7769)))
(apply 'command (append '("pline") coords '("c")))
(setq currobj (ssadd (entlast) currobj))
(setq coords (list 
(list 4159.4375 396.6339) 
(list 4085.415 397.0839) 
(list 4085.415 396.9069) 
(list 4159.4375 396.5569)))
(apply 'command (append '("pline") coords '("c")))
(setq currobj (ssadd (entlast) currobj))
(setq coords (list 
(list 4159.4375 396.4139) 
(list 4085.415 396.7639) 
(list 4085.415 396.5869) 
(list 4159.4375 396.3369)))
(apply 'command (append '("pline") coords '("c")))
(setq currobj (ssadd (entlast) currobj))
(setq coords (list 
(list 4159.4375 396.1939) 
(list 4085.415 396.4439) 
(list 4085.415 396.2669) 
(list 4159.4375 396.1169)))
(apply 'command (append '("pline") coords '("c")))
(setq currobj (ssadd (entlast) currobj))
(setq coords (list 
(list 4159.4375 395.9739) 
(list 4085.415 396.1239) 
(list 4085.415 395.9469) 
(list 4159.4375 395.8969)))
(apply 'command (append '("pline") coords '("c")))
(setq currobj (ssadd (entlast) currobj))
(setq coords (list 
(list 4159.4375 395.7539) 
(list 4085.415 395.8039) 
(list 4085.415 395.6269) 
(list 4159.4375 395.6769)))
(apply 'command (append '("pline") coords '("c")))
(setq currobj (ssadd (entlast) currobj))
(setq coords (list 
(list 4159.4375 395.5339) 
(list 4085.415 395.4839) 
(list 4085.415 395.3069) 
(list 4159.4375 395.4569)))
(apply 'command (append '("pline") coords '("c")))
(setq currobj (ssadd (entlast) currobj))
(setq coords (list 
(list 4159.4375 395.3139) 
(list 4085.415 395.1639) 
(list 4085.415 394.9869) 
(list 4159.4375 395.2369)))
(apply 'command (append '("pline") coords '("c")))
(setq currobj (ssadd (entlast) currobj))
(setq coords (list 
(list 4159.4375 395.0939) 
(list 4085.415 394.8439) 
(list 4085.415 394.6669) 
(list 4159.4375 395.0169)))
(apply 'command (append '("pline") coords '("c")))
(setq currobj (ssadd (entlast) currobj))
(setq coords (list 
(list 4159.4375 394.8739) 
(list 4085.415 394.5239) 
(list 4085.415 394.3469) 
(list 4159.4375 394.7969)))
(apply 'command (append '("pline") coords '("c")))
(setq currobj (ssadd (entlast) currobj))
(setq coords (list 
(list 4159.4375 394.6539) 
(list 4085.415 394.2039) 
(list 4085.415 394.0269) 
(list 4159.4375 394.5769)))
(apply 'command (append '("pline") coords '("c")))
(setq currobj (ssadd (entlast) currobj))
(setq coords (list 
(list 4159.4375 394.4339) 
(list 4085.415 393.8839) 
(list 4085.415 393.7069) 
(list 4159.4375 394.3569)))
(apply 'command (append '("pline") coords '("c")))
(setq currobj (ssadd (entlast) currobj))
(setq coords (list 
(list 4159.4375 394.2139) 
(list 4085.415 393.5639) 
(list 4085.415 393.3869) 
(list 4159.4375 394.1369)))
(apply 'command (append '("pline") coords '("c")))
(setq currobj (ssadd (entlast) currobj))
(command "_layer" "set" "nitride" "")
(command "_layer" "set" "text" "")
(command "_circle" "4159.0625,382.9939" "0.075")
(command "_circle" "4159.0625,383.2939" "0.075")
(command "_circle" "4159.0625,383.5939" "0.075")
(command "_circle" "4159.0625,383.8939" "0.075")
(command "_circle" "4159.0625,384.1939" "0.075")
(command "_circle" "4158.7625,382.9939" "0.075")
(command "_circle" "4158.7625,383.2939" "0.075")
(command "_circle" "4158.7625,383.5939" "0.075")
(command "_circle" "4158.7625,383.8939" "0.075")
(command "_circle" "4158.7625,384.1939" "0.075")
(command "_circle" "4158.4625,382.9939" "0.075")
(command "_circle" "4158.4625,383.2939" "0.075")
(command "_circle" "4158.4625,383.5939" "0.075")
(command "_circle" "4158.4625,383.8939" "0.075")
(command "_circle" "4158.4625,384.1939" "0.075")
(command "_circle" "4158.1625,382.9939" "0.075")
(command "_circle" "4158.1625,383.2939" "0.075")
(command "_circle" "4158.1625,383.5939" "0.075")
(command "_circle" "4158.1625,383.8939" "0.075")
(command "_circle" "4158.1625,384.1939" "0.075")
(command "_circle" "4157.8625,382.9939" "0.075")
(command "_circle" "4157.8625,383.2939" "0.075")
(command "_circle" "4157.8625,383.5939" "0.075")
(command "_circle" "4157.8625,383.8939" "0.075")
(command "_circle" "4157.8625,384.1939" "0.075")
(command "_layer" "set" "nitride" "")
(setq coords (list 
(list 4160.2625 408.4369) 
(list 4160.2625 524.0816) 
(list 4159.7375 524.0816) 
(list 4159.7375 408.4369)))
(apply 'command (append '("pline") coords '("c")))
(setq currobj (ssadd (entlast) currobj))
(command "_layer" "set" "prebias" "")
(command "_rectangle" "4159.7375,408.4369" "4160.2625,524.0816")
(setq currobj (ssadd (entlast) currobj))
(command "_layer" "set" "nitride" "")
(setq coords (list 
(list 4160.2625 524.0816) 
(list 4160.5625 534.0816) 
(list 4160.5625 534.0816) 
(list 4160.5625 535.0816) 
(list 4234.585 534.3316) 
(list 4234.585 539.2746) 
(list 4160.5625 538.5246) 
(list 4160.5625 539.5246) 
(list 4160.5625 539.5246) 
(list 4160.2625 549.5246) 
(list 4159.7375 549.5246) 
(list 4159.4375 539.5246) 
(list 4159.4375 539.5246) 
(list 4159.4375 538.5246) 
(list 4085.415 539.2746) 
(list 4085.415 534.3316) 
(list 4159.4375 535.0816) 
(list 4159.4375 534.0816) 
(list 4159.4375 534.0816) 
(list 4159.7375 524.0816)))
(apply 'command (append '("pline") coords '("c")))
(setq currobj (ssadd (entlast) currobj))
(command "_layer" "set" "prebias" "")
(setq coords (list 
(list 4159.4375 524.0816) 
(list 4159.4375 535.0816) 
(list 4085.415 534.3316) 
(list 4085.415 539.2746) 
(list 4159.4375 538.5246) 
(list 4159.4375 549.5246) 
(list 4160.5625 549.5246) 
(list 4160.5625 538.5246) 
(list 4234.585 539.2746) 
(list 4234.585 534.3316) 
(list 4160.5625 535.0816) 
(list 4160.5625 524.0816)))
(apply 'command (append '("pline") coords '("c")))
(setq currobj (ssadd (entlast) currobj))
(command "_layer" "set" "nitride" "")
(command "_layer" "set" "fda1" "")
(setq coords (list 
(list 4160.5625 535.2246) 
(list 4234.585 534.4746) 
(list 4234.585 534.6516) 
(list 4160.5625 535.3016)))
(apply 'command (append '("pline") coords '("c")))
(setq currobj (ssadd (entlast) currobj))
(setq coords (list 
(list 4160.5625 535.4446) 
(list 4234.585 534.7946) 
(list 4234.585 534.9716) 
(list 4160.5625 535.5216)))
(apply 'command (append '("pline") coords '("c")))
(setq currobj (ssadd (entlast) currobj))
(setq coords (list 
(list 4160.5625 535.6646) 
(list 4234.585 535.1146) 
(list 4234.585 535.2916) 
(list 4160.5625 535.7416)))
(apply 'command (append '("pline") coords '("c")))
(setq currobj (ssadd (entlast) currobj))
(setq coords (list 
(list 4160.5625 535.8846) 
(list 4234.585 535.4346) 
(list 4234.585 535.6116) 
(list 4160.5625 535.9616)))
(apply 'command (append '("pline") coords '("c")))
(setq currobj (ssadd (entlast) currobj))
(setq coords (list 
(list 4160.5625 536.1046) 
(list 4234.585 535.7546) 
(list 4234.585 535.9316) 
(list 4160.5625 536.1816)))
(apply 'command (append '("pline") coords '("c")))
(setq currobj (ssadd (entlast) currobj))
(setq coords (list 
(list 4160.5625 536.3246) 
(list 4234.585 536.0746) 
(list 4234.585 536.2516) 
(list 4160.5625 536.4016)))
(apply 'command (append '("pline") coords '("c")))
(setq currobj (ssadd (entlast) currobj))
(setq coords (list 
(list 4160.5625 536.5446) 
(list 4234.585 536.3946) 
(list 4234.585 536.5716) 
(list 4160.5625 536.6216)))
(apply 'command (append '("pline") coords '("c")))
(setq currobj (ssadd (entlast) currobj))
(setq coords (list 
(list 4160.5625 536.7646) 
(list 4234.585 536.7146) 
(list 4234.585 536.8916) 
(list 4160.5625 536.8416)))
(apply 'command (append '("pline") coords '("c")))
(setq currobj (ssadd (entlast) currobj))
(setq coords (list 
(list 4160.5625 536.9846) 
(list 4234.585 537.0346) 
(list 4234.585 537.2116) 
(list 4160.5625 537.0616)))
(apply 'command (append '("pline") coords '("c")))
(setq currobj (ssadd (entlast) currobj))
(setq coords (list 
(list 4160.5625 537.2046) 
(list 4234.585 537.3546) 
(list 4234.585 537.5316) 
(list 4160.5625 537.2816)))
(apply 'command (append '("pline") coords '("c")))
(setq currobj (ssadd (entlast) currobj))
(setq coords (list 
(list 4160.5625 537.4246) 
(list 4234.585 537.6746) 
(list 4234.585 537.8516) 
(list 4160.5625 537.5016)))
(apply 'command (append '("pline") coords '("c")))
(setq currobj (ssadd (entlast) currobj))
(setq coords (list 
(list 4160.5625 537.6446) 
(list 4234.585 537.9946) 
(list 4234.585 538.1716) 
(list 4160.5625 537.7216)))
(apply 'command (append '("pline") coords '("c")))
(setq currobj (ssadd (entlast) currobj))
(setq coords (list 
(list 4160.5625 537.8646) 
(list 4234.585 538.3146) 
(list 4234.585 538.4916) 
(list 4160.5625 537.9416)))
(apply 'command (append '("pline") coords '("c")))
(setq currobj (ssadd (entlast) currobj))
(setq coords (list 
(list 4160.5625 538.0846) 
(list 4234.585 538.6346) 
(list 4234.585 538.8116) 
(list 4160.5625 538.1616)))
(apply 'command (append '("pline") coords '("c")))
(setq currobj (ssadd (entlast) currobj))
(setq coords (list 
(list 4160.5625 538.3046) 
(list 4234.585 538.9546) 
(list 4234.585 539.1316) 
(list 4160.5625 538.3816)))
(apply 'command (append '("pline") coords '("c")))
(setq currobj (ssadd (entlast) currobj))
(setq coords (list 
(list 4159.4375 538.3816) 
(list 4085.415 539.1316) 
(list 4085.415 538.9546) 
(list 4159.4375 538.3046)))
(apply 'command (append '("pline") coords '("c")))
(setq currobj (ssadd (entlast) currobj))
(setq coords (list 
(list 4159.4375 538.1616) 
(list 4085.415 538.8116) 
(list 4085.415 538.6346) 
(list 4159.4375 538.0846)))
(apply 'command (append '("pline") coords '("c")))
(setq currobj (ssadd (entlast) currobj))
(setq coords (list 
(list 4159.4375 537.9416) 
(list 4085.415 538.4916) 
(list 4085.415 538.3146) 
(list 4159.4375 537.8646)))
(apply 'command (append '("pline") coords '("c")))
(setq currobj (ssadd (entlast) currobj))
(setq coords (list 
(list 4159.4375 537.7216) 
(list 4085.415 538.1716) 
(list 4085.415 537.9946) 
(list 4159.4375 537.6446)))
(apply 'command (append '("pline") coords '("c")))
(setq currobj (ssadd (entlast) currobj))
(setq coords (list 
(list 4159.4375 537.5016) 
(list 4085.415 537.8516) 
(list 4085.415 537.6746) 
(list 4159.4375 537.4246)))
(apply 'command (append '("pline") coords '("c")))
(setq currobj (ssadd (entlast) currobj))
(setq coords (list 
(list 4159.4375 537.2816) 
(list 4085.415 537.5316) 
(list 4085.415 537.3546) 
(list 4159.4375 537.2046)))
(apply 'command (append '("pline") coords '("c")))
(setq currobj (ssadd (entlast) currobj))
(setq coords (list 
(list 4159.4375 537.0616) 
(list 4085.415 537.2116) 
(list 4085.415 537.0346) 
(list 4159.4375 536.9846)))
(apply 'command (append '("pline") coords '("c")))
(setq currobj (ssadd (entlast) currobj))
(setq coords (list 
(list 4159.4375 536.8416) 
(list 4085.415 536.8916) 
(list 4085.415 536.7146) 
(list 4159.4375 536.7646)))
(apply 'command (append '("pline") coords '("c")))
(setq currobj (ssadd (entlast) currobj))
(setq coords (list 
(list 4159.4375 536.6216) 
(list 4085.415 536.5716) 
(list 4085.415 536.3946) 
(list 4159.4375 536.5446)))
(apply 'command (append '("pline") coords '("c")))
(setq currobj (ssadd (entlast) currobj))
(setq coords (list 
(list 4159.4375 536.4016) 
(list 4085.415 536.2516) 
(list 4085.415 536.0746) 
(list 4159.4375 536.3246)))
(apply 'command (append '("pline") coords '("c")))
(setq currobj (ssadd (entlast) currobj))
(setq coords (list 
(list 4159.4375 536.1816) 
(list 4085.415 535.9316) 
(list 4085.415 535.7546) 
(list 4159.4375 536.1046)))
(apply 'command (append '("pline") coords '("c")))
(setq currobj (ssadd (entlast) currobj))
(setq coords (list 
(list 4159.4375 535.9616) 
(list 4085.415 535.6116) 
(list 4085.415 535.4346) 
(list 4159.4375 535.8846)))
(apply 'command (append '("pline") coords '("c")))
(setq currobj (ssadd (entlast) currobj))
(setq coords (list 
(list 4159.4375 535.7416) 
(list 4085.415 535.2916) 
(list 4085.415 535.1146) 
(list 4159.4375 535.6646)))
(apply 'command (append '("pline") coords '("c")))
(setq currobj (ssadd (entlast) currobj))
(setq coords (list 
(list 4159.4375 535.5216) 
(list 4085.415 534.9716) 
(list 4085.415 534.7946) 
(list 4159.4375 535.4446)))
(apply 'command (append '("pline") coords '("c")))
(setq currobj (ssadd (entlast) currobj))
(setq coords (list 
(list 4159.4375 535.3016) 
(list 4085.415 534.6516) 
(list 4085.415 534.4746) 
(list 4159.4375 535.2246)))
(apply 'command (append '("pline") coords '("c")))
(setq currobj (ssadd (entlast) currobj))
(command "_layer" "set" "nitride" "")
(command "_layer" "set" "text" "")
(command "_circle" "4159.0625,524.0816" "0.075")
(command "_circle" "4159.0625,524.3816" "0.075")
(command "_circle" "4159.0625,524.6816" "0.075")
(command "_circle" "4159.0625,524.9816" "0.075")
(command "_circle" "4159.0625,525.2816" "0.075")
(command "_circle" "4158.7625,524.0816" "0.075")
(command "_circle" "4158.7625,524.3816" "0.075")
(command "_circle" "4158.7625,524.6816" "0.075")
(command "_circle" "4158.7625,524.9816" "0.075")
(command "_circle" "4158.7625,525.2816" "0.075")
(command "_circle" "4158.4625,524.0816" "0.075")
(command "_circle" "4158.4625,524.3816" "0.075")
(command "_circle" "4158.4625,524.6816" "0.075")
(command "_circle" "4158.4625,524.9816" "0.075")
(command "_circle" "4158.4625,525.2816" "0.075")
(command "_circle" "4158.1625,524.0816" "0.075")
(command "_circle" "4158.1625,524.3816" "0.075")
(command "_circle" "4158.1625,524.6816" "0.075")
(command "_circle" "4158.1625,524.9816" "0.075")
(command "_circle" "4158.1625,525.2816" "0.075")
(command "_circle" "4157.8625,524.0816" "0.075")
(command "_circle" "4157.8625,524.3816" "0.075")
(command "_circle" "4157.8625,524.6816" "0.075")
(command "_circle" "4157.8625,524.9816" "0.075")
(command "_circle" "4157.8625,525.2816" "0.075")
(command "_layer" "set" "nitride" "")
(setq coords (list 
(list 4160.2625 549.5246) 
(list 4160.2625 665.1693) 
(list 4159.7375 665.1693) 
(list 4159.7375 549.5246)))
(apply 'command (append '("pline") coords '("c")))
(setq currobj (ssadd (entlast) currobj))
(command "_layer" "set" "prebias" "")
(command "_rectangle" "4159.7375,549.5246" "4160.2625,665.1693")
(setq currobj (ssadd (entlast) currobj))
(command "_layer" "set" "nitride" "")
(setq coords (list 
(list 4160.2625 665.1693) 
(list 4160.5625 675.1693) 
(list 4160.5625 675.1693) 
(list 4160.5625 676.1693) 
(list 4234.585 675.4193) 
(list 4234.585 680.3623) 
(list 4160.5625 679.6123) 
(list 4160.5625 680.6123) 
(list 4160.5625 680.6123) 
(list 4160.2625 690.6123) 
(list 4159.7375 690.6123) 
(list 4159.4375 680.6123) 
(list 4159.4375 680.6123) 
(list 4159.4375 679.6123) 
(list 4085.415 680.3623) 
(list 4085.415 675.4193) 
(list 4159.4375 676.1693) 
(list 4159.4375 675.1693) 
(list 4159.4375 675.1693) 
(list 4159.7375 665.1693)))
(apply 'command (append '("pline") coords '("c")))
(setq currobj (ssadd (entlast) currobj))
(command "_layer" "set" "prebias" "")
(setq coords (list 
(list 4159.4375 665.1693) 
(list 4159.4375 676.1693) 
(list 4085.415 675.4193) 
(list 4085.415 680.3623) 
(list 4159.4375 679.6123) 
(list 4159.4375 690.6123) 
(list 4160.5625 690.6123) 
(list 4160.5625 679.6123) 
(list 4234.585 680.3623) 
(list 4234.585 675.4193) 
(list 4160.5625 676.1693) 
(list 4160.5625 665.1693)))
(apply 'command (append '("pline") coords '("c")))
(setq currobj (ssadd (entlast) currobj))
(command "_layer" "set" "nitride" "")
(command "_layer" "set" "fda1" "")
(setq coords (list 
(list 4160.5625 676.3123) 
(list 4234.585 675.5623) 
(list 4234.585 675.7393) 
(list 4160.5625 676.3893)))
(apply 'command (append '("pline") coords '("c")))
(setq currobj (ssadd (entlast) currobj))
(setq coords (list 
(list 4160.5625 676.5323) 
(list 4234.585 675.8823) 
(list 4234.585 676.0593) 
(list 4160.5625 676.6093)))
(apply 'command (append '("pline") coords '("c")))
(setq currobj (ssadd (entlast) currobj))
(setq coords (list 
(list 4160.5625 676.7523) 
(list 4234.585 676.2023) 
(list 4234.585 676.3793) 
(list 4160.5625 676.8293)))
(apply 'command (append '("pline") coords '("c")))
(setq currobj (ssadd (entlast) currobj))
(setq coords (list 
(list 4160.5625 676.9723) 
(list 4234.585 676.5223) 
(list 4234.585 676.6993) 
(list 4160.5625 677.0493)))
(apply 'command (append '("pline") coords '("c")))
(setq currobj (ssadd (entlast) currobj))
(setq coords (list 
(list 4160.5625 677.1923) 
(list 4234.585 676.8423) 
(list 4234.585 677.0193) 
(list 4160.5625 677.2693)))
(apply 'command (append '("pline") coords '("c")))
(setq currobj (ssadd (entlast) currobj))
(setq coords (list 
(list 4160.5625 677.4123) 
(list 4234.585 677.1623) 
(list 4234.585 677.3393) 
(list 4160.5625 677.4893)))
(apply 'command (append '("pline") coords '("c")))
(setq currobj (ssadd (entlast) currobj))
(setq coords (list 
(list 4160.5625 677.6323) 
(list 4234.585 677.4823) 
(list 4234.585 677.6593) 
(list 4160.5625 677.7093)))
(apply 'command (append '("pline") coords '("c")))
(setq currobj (ssadd (entlast) currobj))
(setq coords (list 
(list 4160.5625 677.8523) 
(list 4234.585 677.8023) 
(list 4234.585 677.9793) 
(list 4160.5625 677.9293)))
(apply 'command (append '("pline") coords '("c")))
(setq currobj (ssadd (entlast) currobj))
(setq coords (list 
(list 4160.5625 678.0723) 
(list 4234.585 678.1223) 
(list 4234.585 678.2993) 
(list 4160.5625 678.1493)))
(apply 'command (append '("pline") coords '("c")))
(setq currobj (ssadd (entlast) currobj))
(setq coords (list 
(list 4160.5625 678.2923) 
(list 4234.585 678.4423) 
(list 4234.585 678.6193) 
(list 4160.5625 678.3693)))
(apply 'command (append '("pline") coords '("c")))
(setq currobj (ssadd (entlast) currobj))
(setq coords (list 
(list 4160.5625 678.5123) 
(list 4234.585 678.7623) 
(list 4234.585 678.9393) 
(list 4160.5625 678.5893)))
(apply 'command (append '("pline") coords '("c")))
(setq currobj (ssadd (entlast) currobj))
(setq coords (list 
(list 4160.5625 678.7323) 
(list 4234.585 679.0823) 
(list 4234.585 679.2593) 
(list 4160.5625 678.8093)))
(apply 'command (append '("pline") coords '("c")))
(setq currobj (ssadd (entlast) currobj))
(setq coords (list 
(list 4160.5625 678.9523) 
(list 4234.585 679.4023) 
(list 4234.585 679.5793) 
(list 4160.5625 679.0293)))
(apply 'command (append '("pline") coords '("c")))
(setq currobj (ssadd (entlast) currobj))
(setq coords (list 
(list 4160.5625 679.1723) 
(list 4234.585 679.7223) 
(list 4234.585 679.8993) 
(list 4160.5625 679.2493)))
(apply 'command (append '("pline") coords '("c")))
(setq currobj (ssadd (entlast) currobj))
(setq coords (list 
(list 4160.5625 679.3923) 
(list 4234.585 680.0423) 
(list 4234.585 680.2193) 
(list 4160.5625 679.4693)))
(apply 'command (append '("pline") coords '("c")))
(setq currobj (ssadd (entlast) currobj))
(setq coords (list 
(list 4159.4375 679.4693) 
(list 4085.415 680.2193) 
(list 4085.415 680.0423) 
(list 4159.4375 679.3923)))
(apply 'command (append '("pline") coords '("c")))
(setq currobj (ssadd (entlast) currobj))
(setq coords (list 
(list 4159.4375 679.2493) 
(list 4085.415 679.8993) 
(list 4085.415 679.7223) 
(list 4159.4375 679.1723)))
(apply 'command (append '("pline") coords '("c")))
(setq currobj (ssadd (entlast) currobj))
(setq coords (list 
(list 4159.4375 679.0293) 
(list 4085.415 679.5793) 
(list 4085.415 679.4023) 
(list 4159.4375 678.9523)))
(apply 'command (append '("pline") coords '("c")))
(setq currobj (ssadd (entlast) currobj))
(setq coords (list 
(list 4159.4375 678.8093) 
(list 4085.415 679.2593) 
(list 4085.415 679.0823) 
(list 4159.4375 678.7323)))
(apply 'command (append '("pline") coords '("c")))
(setq currobj (ssadd (entlast) currobj))
(setq coords (list 
(list 4159.4375 678.5893) 
(list 4085.415 678.9393) 
(list 4085.415 678.7623) 
(list 4159.4375 678.5123)))
(apply 'command (append '("pline") coords '("c")))
(setq currobj (ssadd (entlast) currobj))
(setq coords (list 
(list 4159.4375 678.3693) 
(list 4085.415 678.6193) 
(list 4085.415 678.4423) 
(list 4159.4375 678.2923)))
(apply 'command (append '("pline") coords '("c")))
(setq currobj (ssadd (entlast) currobj))
(setq coords (list 
(list 4159.4375 678.1493) 
(list 4085.415 678.2993) 
(list 4085.415 678.1223) 
(list 4159.4375 678.0723)))
(apply 'command (append '("pline") coords '("c")))
(setq currobj (ssadd (entlast) currobj))
(setq coords (list 
(list 4159.4375 677.9293) 
(list 4085.415 677.9793) 
(list 4085.415 677.8023) 
(list 4159.4375 677.8523)))
(apply 'command (append '("pline") coords '("c")))
(setq currobj (ssadd (entlast) currobj))
(setq coords (list 
(list 4159.4375 677.7093) 
(list 4085.415 677.6593) 
(list 4085.415 677.4823) 
(list 4159.4375 677.6323)))
(apply 'command (append '("pline") coords '("c")))
(setq currobj (ssadd (entlast) currobj))
(setq coords (list 
(list 4159.4375 677.4893) 
(list 4085.415 677.3393) 
(list 4085.415 677.1623) 
(list 4159.4375 677.4123)))
(apply 'command (append '("pline") coords '("c")))
(setq currobj (ssadd (entlast) currobj))
(setq coords (list 
(list 4159.4375 677.2693) 
(list 4085.415 677.0193) 
(list 4085.415 676.8423) 
(list 4159.4375 677.1923)))
(apply 'command (append '("pline") coords '("c")))
(setq currobj (ssadd (entlast) currobj))
(setq coords (list 
(list 4159.4375 677.0493) 
(list 4085.415 676.6993) 
(list 4085.415 676.5223) 
(list 4159.4375 676.9723)))
(apply 'command (append '("pline") coords '("c")))
(setq currobj (ssadd (entlast) currobj))
(setq coords (list 
(list 4159.4375 676.8293) 
(list 4085.415 676.3793) 
(list 4085.415 676.2023) 
(list 4159.4375 676.7523)))
(apply 'command (append '("pline") coords '("c")))
(setq currobj (ssadd (entlast) currobj))
(setq coords (list 
(list 4159.4375 676.6093) 
(list 4085.415 676.0593) 
(list 4085.415 675.8823) 
(list 4159.4375 676.5323)))
(apply 'command (append '("pline") coords '("c")))
(setq currobj (ssadd (entlast) currobj))
(setq coords (list 
(list 4159.4375 676.3893) 
(list 4085.415 675.7393) 
(list 4085.415 675.5623) 
(list 4159.4375 676.3123)))
(apply 'command (append '("pline") coords '("c")))
(setq currobj (ssadd (entlast) currobj))
(command "_layer" "set" "nitride" "")
(command "_layer" "set" "text" "")
(command "_circle" "4159.0625,665.1693" "0.075")
(command "_circle" "4159.0625,665.4693" "0.075")
(command "_circle" "4159.0625,665.7693" "0.075")
(command "_circle" "4159.0625,666.0693" "0.075")
(command "_circle" "4159.0625,666.3693" "0.075")
(command "_circle" "4158.7625,665.1693" "0.075")
(command "_circle" "4158.7625,665.4693" "0.075")
(command "_circle" "4158.7625,665.7693" "0.075")
(command "_circle" "4158.7625,666.0693" "0.075")
(command "_circle" "4158.7625,666.3693" "0.075")
(command "_circle" "4158.4625,665.1693" "0.075")
(command "_circle" "4158.4625,665.4693" "0.075")
(command "_circle" "4158.4625,665.7693" "0.075")
(command "_circle" "4158.4625,666.0693" "0.075")
(command "_circle" "4158.4625,666.3693" "0.075")
(command "_circle" "4158.1625,665.1693" "0.075")
(command "_circle" "4158.1625,665.4693" "0.075")
(command "_circle" "4158.1625,665.7693" "0.075")
(command "_circle" "4158.1625,666.0693" "0.075")
(command "_circle" "4158.1625,666.3693" "0.075")
(command "_circle" "4157.8625,665.1693" "0.075")
(command "_circle" "4157.8625,665.4693" "0.075")
(command "_circle" "4157.8625,665.7693" "0.075")
(command "_circle" "4157.8625,666.0693" "0.075")
(command "_circle" "4157.8625,666.3693" "0.075")
(command "_layer" "set" "nitride" "")
(setq coords (list 
(list 4160.2625 690.6123) 
(list 4160.2625 806.257) 
(list 4159.7375 806.257) 
(list 4159.7375 690.6123)))
(apply 'command (append '("pline") coords '("c")))
(setq currobj (ssadd (entlast) currobj))
(command "_layer" "set" "prebias" "")
(command "_rectangle" "4159.7375,690.6123" "4160.2625,806.257")
(setq currobj (ssadd (entlast) currobj))
(command "_layer" "set" "nitride" "")
(setq coords (list 
(list 4160.2625 806.257) 
(list 4160.5625 816.257) 
(list 4160.5625 816.257) 
(list 4160.5625 817.257) 
(list 4234.585 816.507) 
(list 4234.585 821.45) 
(list 4160.5625 820.7) 
(list 4160.5625 821.7) 
(list 4160.5625 821.7) 
(list 4160.2625 831.7) 
(list 4159.7375 831.7) 
(list 4159.4375 821.7) 
(list 4159.4375 821.7) 
(list 4159.4375 820.7) 
(list 4085.415 821.45) 
(list 4085.415 816.507) 
(list 4159.4375 817.257) 
(list 4159.4375 816.257) 
(list 4159.4375 816.257) 
(list 4159.7375 806.257)))
(apply 'command (append '("pline") coords '("c")))
(setq currobj (ssadd (entlast) currobj))
(command "_layer" "set" "prebias" "")
(setq coords (list 
(list 4159.4375 806.257) 
(list 4159.4375 817.257) 
(list 4085.415 816.507) 
(list 4085.415 821.45) 
(list 4159.4375 820.7) 
(list 4159.4375 831.7) 
(list 4160.5625 831.7) 
(list 4160.5625 820.7) 
(list 4234.585 821.45) 
(list 4234.585 816.507) 
(list 4160.5625 817.257) 
(list 4160.5625 806.257)))
(apply 'command (append '("pline") coords '("c")))
(setq currobj (ssadd (entlast) currobj))
(command "_layer" "set" "nitride" "")
(command "_layer" "set" "fda1" "")
(setq coords (list 
(list 4160.5625 817.4) 
(list 4234.585 816.65) 
(list 4234.585 816.827) 
(list 4160.5625 817.477)))
(apply 'command (append '("pline") coords '("c")))
(setq currobj (ssadd (entlast) currobj))
(setq coords (list 
(list 4160.5625 817.62) 
(list 4234.585 816.97) 
(list 4234.585 817.147) 
(list 4160.5625 817.697)))
(apply 'command (append '("pline") coords '("c")))
(setq currobj (ssadd (entlast) currobj))
(setq coords (list 
(list 4160.5625 817.84) 
(list 4234.585 817.29) 
(list 4234.585 817.467) 
(list 4160.5625 817.917)))
(apply 'command (append '("pline") coords '("c")))
(setq currobj (ssadd (entlast) currobj))
(setq coords (list 
(list 4160.5625 818.06) 
(list 4234.585 817.61) 
(list 4234.585 817.787) 
(list 4160.5625 818.137)))
(apply 'command (append '("pline") coords '("c")))
(setq currobj (ssadd (entlast) currobj))
(setq coords (list 
(list 4160.5625 818.28) 
(list 4234.585 817.93) 
(list 4234.585 818.107) 
(list 4160.5625 818.357)))
(apply 'command (append '("pline") coords '("c")))
(setq currobj (ssadd (entlast) currobj))
(setq coords (list 
(list 4160.5625 818.5) 
(list 4234.585 818.25) 
(list 4234.585 818.427) 
(list 4160.5625 818.577)))
(apply 'command (append '("pline") coords '("c")))
(setq currobj (ssadd (entlast) currobj))
(setq coords (list 
(list 4160.5625 818.72) 
(list 4234.585 818.57) 
(list 4234.585 818.747) 
(list 4160.5625 818.797)))
(apply 'command (append '("pline") coords '("c")))
(setq currobj (ssadd (entlast) currobj))
(setq coords (list 
(list 4160.5625 818.94) 
(list 4234.585 818.89) 
(list 4234.585 819.067) 
(list 4160.5625 819.017)))
(apply 'command (append '("pline") coords '("c")))
(setq currobj (ssadd (entlast) currobj))
(setq coords (list 
(list 4160.5625 819.16) 
(list 4234.585 819.21) 
(list 4234.585 819.387) 
(list 4160.5625 819.237)))
(apply 'command (append '("pline") coords '("c")))
(setq currobj (ssadd (entlast) currobj))
(setq coords (list 
(list 4160.5625 819.38) 
(list 4234.585 819.53) 
(list 4234.585 819.707) 
(list 4160.5625 819.457)))
(apply 'command (append '("pline") coords '("c")))
(setq currobj (ssadd (entlast) currobj))
(setq coords (list 
(list 4160.5625 819.6) 
(list 4234.585 819.85) 
(list 4234.585 820.027) 
(list 4160.5625 819.677)))
(apply 'command (append '("pline") coords '("c")))
(setq currobj (ssadd (entlast) currobj))
(setq coords (list 
(list 4160.5625 819.82) 
(list 4234.585 820.17) 
(list 4234.585 820.347) 
(list 4160.5625 819.897)))
(apply 'command (append '("pline") coords '("c")))
(setq currobj (ssadd (entlast) currobj))
(setq coords (list 
(list 4160.5625 820.04) 
(list 4234.585 820.49) 
(list 4234.585 820.667) 
(list 4160.5625 820.117)))
(apply 'command (append '("pline") coords '("c")))
(setq currobj (ssadd (entlast) currobj))
(setq coords (list 
(list 4160.5625 820.26) 
(list 4234.585 820.81) 
(list 4234.585 820.987) 
(list 4160.5625 820.337)))
(apply 'command (append '("pline") coords '("c")))
(setq currobj (ssadd (entlast) currobj))
(setq coords (list 
(list 4160.5625 820.48) 
(list 4234.585 821.13) 
(list 4234.585 821.307) 
(list 4160.5625 820.557)))
(apply 'command (append '("pline") coords '("c")))
(setq currobj (ssadd (entlast) currobj))
(setq coords (list 
(list 4159.4375 820.557) 
(list 4085.415 821.307) 
(list 4085.415 821.13) 
(list 4159.4375 820.48)))
(apply 'command (append '("pline") coords '("c")))
(setq currobj (ssadd (entlast) currobj))
(setq coords (list 
(list 4159.4375 820.337) 
(list 4085.415 820.987) 
(list 4085.415 820.81) 
(list 4159.4375 820.26)))
(apply 'command (append '("pline") coords '("c")))
(setq currobj (ssadd (entlast) currobj))
(setq coords (list 
(list 4159.4375 820.117) 
(list 4085.415 820.667) 
(list 4085.415 820.49) 
(list 4159.4375 820.04)))
(apply 'command (append '("pline") coords '("c")))
(setq currobj (ssadd (entlast) currobj))
(setq coords (list 
(list 4159.4375 819.897) 
(list 4085.415 820.347) 
(list 4085.415 820.17) 
(list 4159.4375 819.82)))
(apply 'command (append '("pline") coords '("c")))
(setq currobj (ssadd (entlast) currobj))
(setq coords (list 
(list 4159.4375 819.677) 
(list 4085.415 820.027) 
(list 4085.415 819.85) 
(list 4159.4375 819.6)))
(apply 'command (append '("pline") coords '("c")))
(setq currobj (ssadd (entlast) currobj))
(setq coords (list 
(list 4159.4375 819.457) 
(list 4085.415 819.707) 
(list 4085.415 819.53) 
(list 4159.4375 819.38)))
(apply 'command (append '("pline") coords '("c")))
(setq currobj (ssadd (entlast) currobj))
(setq coords (list 
(list 4159.4375 819.237) 
(list 4085.415 819.387) 
(list 4085.415 819.21) 
(list 4159.4375 819.16)))
(apply 'command (append '("pline") coords '("c")))
(setq currobj (ssadd (entlast) currobj))
(setq coords (list 
(list 4159.4375 819.017) 
(list 4085.415 819.067) 
(list 4085.415 818.89) 
(list 4159.4375 818.94)))
(apply 'command (append '("pline") coords '("c")))
(setq currobj (ssadd (entlast) currobj))
(setq coords (list 
(list 4159.4375 818.797) 
(list 4085.415 818.747) 
(list 4085.415 818.57) 
(list 4159.4375 818.72)))
(apply 'command (append '("pline") coords '("c")))
(setq currobj (ssadd (entlast) currobj))
(setq coords (list 
(list 4159.4375 818.577) 
(list 4085.415 818.427) 
(list 4085.415 818.25) 
(list 4159.4375 818.5)))
(apply 'command (append '("pline") coords '("c")))
(setq currobj (ssadd (entlast) currobj))
(setq coords (list 
(list 4159.4375 818.357) 
(list 4085.415 818.107) 
(list 4085.415 817.93) 
(list 4159.4375 818.28)))
(apply 'command (append '("pline") coords '("c")))
(setq currobj (ssadd (entlast) currobj))
(setq coords (list 
(list 4159.4375 818.137) 
(list 4085.415 817.787) 
(list 4085.415 817.61) 
(list 4159.4375 818.06)))
(apply 'command (append '("pline") coords '("c")))
(setq currobj (ssadd (entlast) currobj))
(setq coords (list 
(list 4159.4375 817.917) 
(list 4085.415 817.467) 
(list 4085.415 817.29) 
(list 4159.4375 817.84)))
(apply 'command (append '("pline") coords '("c")))
(setq currobj (ssadd (entlast) currobj))
(setq coords (list 
(list 4159.4375 817.697) 
(list 4085.415 817.147) 
(list 4085.415 816.97) 
(list 4159.4375 817.62)))
(apply 'command (append '("pline") coords '("c")))
(setq currobj (ssadd (entlast) currobj))
(setq coords (list 
(list 4159.4375 817.477) 
(list 4085.415 816.827) 
(list 4085.415 816.65) 
(list 4159.4375 817.4)))
(apply 'command (append '("pline") coords '("c")))
(setq currobj (ssadd (entlast) currobj))
(command "_layer" "set" "nitride" "")
(command "_layer" "set" "text" "")
(command "_circle" "4159.0625,806.257" "0.075")
(command "_circle" "4159.0625,806.557" "0.075")
(command "_circle" "4159.0625,806.857" "0.075")
(command "_circle" "4159.0625,807.157" "0.075")
(command "_circle" "4159.0625,807.457" "0.075")
(command "_circle" "4158.7625,806.257" "0.075")
(command "_circle" "4158.7625,806.557" "0.075")
(command "_circle" "4158.7625,806.857" "0.075")
(command "_circle" "4158.7625,807.157" "0.075")
(command "_circle" "4158.7625,807.457" "0.075")
(command "_circle" "4158.4625,806.257" "0.075")
(command "_circle" "4158.4625,806.557" "0.075")
(command "_circle" "4158.4625,806.857" "0.075")
(command "_circle" "4158.4625,807.157" "0.075")
(command "_circle" "4158.4625,807.457" "0.075")
(command "_circle" "4158.1625,806.257" "0.075")
(command "_circle" "4158.1625,806.557" "0.075")
(command "_circle" "4158.1625,806.857" "0.075")
(command "_circle" "4158.1625,807.157" "0.075")
(command "_circle" "4158.1625,807.457" "0.075")
(command "_circle" "4157.8625,806.257" "0.075")
(command "_circle" "4157.8625,806.557" "0.075")
(command "_circle" "4157.8625,806.857" "0.075")
(command "_circle" "4157.8625,807.157" "0.075")
(command "_circle" "4157.8625,807.457" "0.075")
(command "_layer" "set" "nitride" "")
(setq coords (list 
(list 4160.2625 831.7) 
(list 4160.2625 836.7) 
(list 4159.7375 836.7) 
(list 4159.7375 831.7)))
(apply 'command (append '("pline") coords '("c")))
(setq currobj (ssadd (entlast) currobj))
(command "_layer" "set" "prebias" "")
(command "_rectangle" "4159.7375,831.7" "4160.2625,836.7")
(setq currobj (ssadd (entlast) currobj))
(command "_layer" "set" "nitride" "")
(setq cooledsinglenanobeam13 currobj)
(setq currobj nil)
(setq currobj (ssadd))
; DRAWING PHOTONIC CRYSTAL
(command "_layer" "set" "negYjunc" "")
(setq coords (list 
(list 4160.125 866.7) 
(list 4160 851.7) 
(list 4160 866.7)))
(apply 'command (append '("pline") coords '("c")))
(setq currobj (ssadd (entlast) currobj))
(setq coords (list 
(list 4160.2625 836.7) 
(list 4160.405 866.7) 
(list 4161.112 866.7) 
(list 4161.112 836.7)))
(apply 'command (append '("pline") coords '("c")))
(setq currobj (ssadd (entlast) currobj))
(setq coords (list 
(list 4159.875 866.7) 
(list 4160 851.7) 
(list 4160 866.7)))
(apply 'command (append '("pline") coords '("c")))
(setq currobj (ssadd (entlast) currobj))
(setq coords (list 
(list 4159.7375 836.7) 
(list 4159.595 866.7) 
(list 4158.888 866.7) 
(list 4158.888 836.7)))
(apply 'command (append '("pline") coords '("c")))
(setq currobj (ssadd (entlast) currobj))
(command "_layer" "set" "nitride" "")
(setq yjunction13 currobj)
(setq currobj nil)
(setq currobj (ssadd))
(setq tap13 nil)
(setq tap13 (ssadd))
(command "_layer" "set" "phc" "")
(setq coords (list 
(list 4160 866.7) 
(list 4160.125 866.7) 
(list 4160.125 866.7103) 
(list 4160.125 866.7206) 
(list 4160.125 866.7308) 
(list 4160.125 866.7411) 
(list 4160.125 866.7514) 
(list 4160.125 866.7617) 
(list 4160.125 866.7719) 
(list 4160.125 866.7822) 
(list 4160.125 866.7925) 
(list 4160.125 866.8028) 
(list 4160.125 866.8131) 
(list 4160.125 866.8233) 
(list 4160.125 866.8336) 
(list 4160.125 866.8439) 
(list 4160.125 866.8542) 
(list 4160.125 866.8644) 
(list 4160.125 866.8747) 
(list 4160.125 866.885) 
(list 4160.125 866.8953) 
(list 4160.125 866.9056) 
(list 4160.125 866.9158) 
(list 4160.125 866.9261) 
(list 4160.125 866.9364) 
(list 4160.125 866.9467) 
(list 4160.125 866.9569) 
(list 4160.125 866.9672) 
(list 4160.125 866.9775) 
(list 4160.125 866.9878) 
(list 4160.125 866.9981) 
(list 4160.125 867.0083) 
(list 4160.125 867.0186) 
(list 4160.125 867.0289) 
(list 4160.125 867.0392) 
(list 4160.125 867.0494) 
(list 4160.125 867.0597) 
(list 4160.125 867.07) 
(list 4160 867.07)))
(apply 'command (append '("pline") coords '("c")))
(setq tap13 (ssadd (entlast) tap13))
(command "_mirror" (entlast) "" "4160,900" "4160,901" "No")
(setq tap13 (ssadd (entlast) tap13))
(setq coords (list 
(list 4160.4151 866.7) 
(list 4160.405 866.7) 
(list 4160.4053 866.7103) 
(list 4160.4055 866.7206) 
(list 4160.4057 866.7308) 
(list 4160.4059 866.7411) 
(list 4160.406 866.7514) 
(list 4160.406 866.7617) 
(list 4160.4059 866.7719) 
(list 4160.4057 866.7822) 
(list 4160.4054 866.7925) 
(list 4160.405 866.8028) 
(list 4160.4046 866.8131) 
(list 4160.4041 866.8233) 
(list 4160.4036 866.8336) 
(list 4160.4031 866.8439) 
(list 4160.4026 866.8542) 
(list 4160.4022 866.8644) 
(list 4160.4018 866.8747) 
(list 4160.4016 866.885) 
(list 4160.4014 866.8953) 
(list 4160.4015 866.9056) 
(list 4160.4017 866.9158) 
(list 4160.402 866.9261) 
(list 4160.4025 866.9364) 
(list 4160.4032 866.9467) 
(list 4160.4041 866.9569) 
(list 4160.4051 866.9672) 
(list 4160.4062 866.9775) 
(list 4160.4074 866.9878) 
(list 4160.4086 866.9981) 
(list 4160.4099 867.0083) 
(list 4160.4111 867.0186) 
(list 4160.4122 867.0289) 
(list 4160.4132 867.0392) 
(list 4160.414 867.0494) 
(list 4160.4147 867.0597) 
(list 4160.4151 867.07) 
(list 4160.4151 867.07)))
(apply 'command (append '("pline") coords '("c")))
(setq tap13 (ssadd (entlast) tap13))
(command "_mirror" (entlast) "" "4160,900" "4160,901" "No")
(setq tap13 (ssadd (entlast) tap13))
(setq coords (list 
(list 4161.112 866.7) 
(list 4160.4151 866.7) 
(list 4160.4151 866.7103) 
(list 4160.4151 866.7206) 
(list 4160.4151 866.7308) 
(list 4160.4151 866.7411) 
(list 4160.4151 866.7514) 
(list 4160.4151 866.7617) 
(list 4160.4151 866.7719) 
(list 4160.4151 866.7822) 
(list 4160.4151 866.7925) 
(list 4160.4151 866.8028) 
(list 4160.4151 866.8131) 
(list 4160.4151 866.8233) 
(list 4160.4151 866.8336) 
(list 4160.4151 866.8439) 
(list 4160.4151 866.8542) 
(list 4160.4151 866.8644) 
(list 4160.4151 866.8747) 
(list 4160.4151 866.885) 
(list 4160.4151 866.8953) 
(list 4160.4151 866.9056) 
(list 4160.4151 866.9158) 
(list 4160.4151 866.9261) 
(list 4160.4151 866.9364) 
(list 4160.4151 866.9467) 
(list 4160.4151 866.9569) 
(list 4160.4151 866.9672) 
(list 4160.4151 866.9775) 
(list 4160.4151 866.9878) 
(list 4160.4151 866.9981) 
(list 4160.4151 867.0083) 
(list 4160.4151 867.0186) 
(list 4160.4151 867.0289) 
(list 4160.4151 867.0392) 
(list 4160.4151 867.0494) 
(list 4160.4151 867.0597) 
(list 4160.4151 867.07) 
(list 4161.112 867.07)))
(apply 'command (append '("pline") coords '("c")))
(setq tap13 (ssadd (entlast) tap13))
(command "_mirror" (entlast) "" "4160,900" "4160,901" "No")
(setq tap13 (ssadd (entlast) tap13))
(setq coords (list 
(list 4160 867.07) 
(list 4160.125 867.07) 
(list 4160.125 867.0803) 
(list 4160.125 867.0906) 
(list 4160.125 867.1008) 
(list 4160.125 867.1111) 
(list 4160.125 867.1214) 
(list 4160.125 867.1317) 
(list 4160.125 867.1419) 
(list 4160.125 867.1522) 
(list 4160.125 867.1625) 
(list 4160.125 867.1728) 
(list 4160.125 867.1831) 
(list 4160.125 867.1933) 
(list 4160.125 867.2036) 
(list 4160.125 867.2139) 
(list 4160.125 867.2242) 
(list 4160.125 867.2344) 
(list 4160.125 867.2447) 
(list 4160.125 867.255) 
(list 4160.125 867.2653) 
(list 4160.125 867.2756) 
(list 4160.125 867.2858) 
(list 4160.125 867.2961) 
(list 4160.125 867.3064) 
(list 4160.125 867.3167) 
(list 4160.125 867.3269) 
(list 4160.125 867.3372) 
(list 4160.125 867.3475) 
(list 4160.125 867.3578) 
(list 4160.125 867.3681) 
(list 4160.125 867.3783) 
(list 4160.125 867.3886) 
(list 4160.125 867.3989) 
(list 4160.125 867.4092) 
(list 4160.125 867.4194) 
(list 4160.125 867.4297) 
(list 4160.125 867.44) 
(list 4160 867.44)))
(apply 'command (append '("pline") coords '("c")))
(setq tap13 (ssadd (entlast) tap13))
(command "_mirror" (entlast) "" "4160,900" "4160,901" "No")
(setq tap13 (ssadd (entlast) tap13))
(setq coords (list 
(list 4160.4251 867.07) 
(list 4160.4151 867.07) 
(list 4160.4152 867.0803) 
(list 4160.4151 867.0906) 
(list 4160.4147 867.1008) 
(list 4160.414 867.1111) 
(list 4160.413 867.1214) 
(list 4160.4118 867.1317) 
(list 4160.4104 867.1419) 
(list 4160.4088 867.1522) 
(list 4160.407 867.1625) 
(list 4160.4052 867.1728) 
(list 4160.4033 867.1831) 
(list 4160.4015 867.1933) 
(list 4160.3998 867.2036) 
(list 4160.3982 867.2139) 
(list 4160.3969 867.2242) 
(list 4160.3958 867.2344) 
(list 4160.3951 867.2447) 
(list 4160.3947 867.255) 
(list 4160.3947 867.2653) 
(list 4160.3951 867.2756) 
(list 4160.3959 867.2858) 
(list 4160.3971 867.2961) 
(list 4160.3987 867.3064) 
(list 4160.4006 867.3167) 
(list 4160.4028 867.3269) 
(list 4160.4052 867.3372) 
(list 4160.4078 867.3475) 
(list 4160.4105 867.3578) 
(list 4160.4131 867.3681) 
(list 4160.4157 867.3783) 
(list 4160.4181 867.3886) 
(list 4160.4203 867.3989) 
(list 4160.4221 867.4092) 
(list 4160.4236 867.4194) 
(list 4160.4246 867.4297) 
(list 4160.4251 867.44) 
(list 4160.4251 867.44)))
(apply 'command (append '("pline") coords '("c")))
(setq tap13 (ssadd (entlast) tap13))
(command "_mirror" (entlast) "" "4160,900" "4160,901" "No")
(setq tap13 (ssadd (entlast) tap13))
(setq coords (list 
(list 4161.112 867.07) 
(list 4160.4251 867.07) 
(list 4160.4251 867.0803) 
(list 4160.4251 867.0906) 
(list 4160.4251 867.1008) 
(list 4160.4251 867.1111) 
(list 4160.4251 867.1214) 
(list 4160.4251 867.1317) 
(list 4160.4251 867.1419) 
(list 4160.4251 867.1522) 
(list 4160.4251 867.1625) 
(list 4160.4251 867.1728) 
(list 4160.4251 867.1831) 
(list 4160.4251 867.1933) 
(list 4160.4251 867.2036) 
(list 4160.4251 867.2139) 
(list 4160.4251 867.2242) 
(list 4160.4251 867.2344) 
(list 4160.4251 867.2447) 
(list 4160.4251 867.255) 
(list 4160.4251 867.2653) 
(list 4160.4251 867.2756) 
(list 4160.4251 867.2858) 
(list 4160.4251 867.2961) 
(list 4160.4251 867.3064) 
(list 4160.4251 867.3167) 
(list 4160.4251 867.3269) 
(list 4160.4251 867.3372) 
(list 4160.4251 867.3475) 
(list 4160.4251 867.3578) 
(list 4160.4251 867.3681) 
(list 4160.4251 867.3783) 
(list 4160.4251 867.3886) 
(list 4160.4251 867.3989) 
(list 4160.4251 867.4092) 
(list 4160.4251 867.4194) 
(list 4160.4251 867.4297) 
(list 4160.4251 867.44) 
(list 4161.112 867.44)))
(apply 'command (append '("pline") coords '("c")))
(setq tap13 (ssadd (entlast) tap13))
(command "_mirror" (entlast) "" "4160,900" "4160,901" "No")
(setq tap13 (ssadd (entlast) tap13))
(setq coords (list 
(list 4160 867.44) 
(list 4160.125 867.44) 
(list 4160.125 867.4503) 
(list 4160.125 867.4606) 
(list 4160.125 867.4708) 
(list 4160.125 867.4811) 
(list 4160.125 867.4914) 
(list 4160.125 867.5017) 
(list 4160.125 867.5119) 
(list 4160.125 867.5222) 
(list 4160.125 867.5325) 
(list 4160.125 867.5428) 
(list 4160.125 867.5531) 
(list 4160.125 867.5633) 
(list 4160.125 867.5736) 
(list 4160.125 867.5839) 
(list 4160.125 867.5942) 
(list 4160.125 867.6044) 
(list 4160.125 867.6147) 
(list 4160.125 867.625) 
(list 4160.125 867.6353) 
(list 4160.125 867.6456) 
(list 4160.125 867.6558) 
(list 4160.125 867.6661) 
(list 4160.125 867.6764) 
(list 4160.125 867.6867) 
(list 4160.125 867.6969) 
(list 4160.125 867.7072) 
(list 4160.125 867.7175) 
(list 4160.125 867.7278) 
(list 4160.125 867.7381) 
(list 4160.125 867.7483) 
(list 4160.125 867.7586) 
(list 4160.125 867.7689) 
(list 4160.125 867.7792) 
(list 4160.125 867.7894) 
(list 4160.125 867.7997) 
(list 4160.125 867.81) 
(list 4160 867.81)))
(apply 'command (append '("pline") coords '("c")))
(setq tap13 (ssadd (entlast) tap13))
(command "_mirror" (entlast) "" "4160,900" "4160,901" "No")
(setq tap13 (ssadd (entlast) tap13))
(setq coords (list 
(list 4160.4352 867.44) 
(list 4160.4251 867.44) 
(list 4160.4252 867.4503) 
(list 4160.4246 867.4606) 
(list 4160.4236 867.4708) 
(list 4160.4221 867.4811) 
(list 4160.4201 867.4914) 
(list 4160.4176 867.5017) 
(list 4160.4149 867.5119) 
(list 4160.4118 867.5222) 
(list 4160.4086 867.5325) 
(list 4160.4053 867.5428) 
(list 4160.402 867.5531) 
(list 4160.3989 867.5633) 
(list 4160.3959 867.5736) 
(list 4160.3933 867.5839) 
(list 4160.3911 867.5942) 
(list 4160.3895 867.6044) 
(list 4160.3883 867.6147) 
(list 4160.3878 867.625) 
(list 4160.388 867.6353) 
(list 4160.3888 867.6456) 
(list 4160.3902 867.6558) 
(list 4160.3922 867.6661) 
(list 4160.3949 867.6764) 
(list 4160.398 867.6867) 
(list 4160.4015 867.6969) 
(list 4160.4054 867.7072) 
(list 4160.4094 867.7175) 
(list 4160.4135 867.7278) 
(list 4160.4176 867.7381) 
(list 4160.4215 867.7483) 
(list 4160.4251 867.7586) 
(list 4160.4284 867.7689) 
(list 4160.4311 867.7792) 
(list 4160.4331 867.7894) 
(list 4160.4345 867.7997) 
(list 4160.4352 867.81) 
(list 4160.4352 867.81)))
(apply 'command (append '("pline") coords '("c")))
(setq tap13 (ssadd (entlast) tap13))
(command "_mirror" (entlast) "" "4160,900" "4160,901" "No")
(setq tap13 (ssadd (entlast) tap13))
(setq coords (list 
(list 4161.112 867.44) 
(list 4160.4352 867.44) 
(list 4160.4352 867.4503) 
(list 4160.4352 867.4606) 
(list 4160.4352 867.4708) 
(list 4160.4352 867.4811) 
(list 4160.4352 867.4914) 
(list 4160.4352 867.5017) 
(list 4160.4352 867.5119) 
(list 4160.4352 867.5222) 
(list 4160.4352 867.5325) 
(list 4160.4352 867.5428) 
(list 4160.4352 867.5531) 
(list 4160.4352 867.5633) 
(list 4160.4352 867.5736) 
(list 4160.4352 867.5839) 
(list 4160.4352 867.5942) 
(list 4160.4352 867.6044) 
(list 4160.4352 867.6147) 
(list 4160.4352 867.625) 
(list 4160.4352 867.6353) 
(list 4160.4352 867.6456) 
(list 4160.4352 867.6558) 
(list 4160.4352 867.6661) 
(list 4160.4352 867.6764) 
(list 4160.4352 867.6867) 
(list 4160.4352 867.6969) 
(list 4160.4352 867.7072) 
(list 4160.4352 867.7175) 
(list 4160.4352 867.7278) 
(list 4160.4352 867.7381) 
(list 4160.4352 867.7483) 
(list 4160.4352 867.7586) 
(list 4160.4352 867.7689) 
(list 4160.4352 867.7792) 
(list 4160.4352 867.7894) 
(list 4160.4352 867.7997) 
(list 4160.4352 867.81) 
(list 4161.112 867.81)))
(apply 'command (append '("pline") coords '("c")))
(setq tap13 (ssadd (entlast) tap13))
(command "_mirror" (entlast) "" "4160,900" "4160,901" "No")
(setq tap13 (ssadd (entlast) tap13))
(setq coords (list 
(list 4160 867.81) 
(list 4160.125 867.81) 
(list 4160.125 867.8203) 
(list 4160.125 867.8306) 
(list 4160.125 867.8408) 
(list 4160.125 867.8511) 
(list 4160.125 867.8614) 
(list 4160.125 867.8717) 
(list 4160.125 867.8819) 
(list 4160.125 867.8922) 
(list 4160.125 867.9025) 
(list 4160.125 867.9128) 
(list 4160.125 867.9231) 
(list 4160.125 867.9333) 
(list 4160.125 867.9436) 
(list 4160.125 867.9539) 
(list 4160.125 867.9642) 
(list 4160.125 867.9744) 
(list 4160.125 867.9847) 
(list 4160.125 867.995) 
(list 4160.125 868.0053) 
(list 4160.125 868.0156) 
(list 4160.125 868.0258) 
(list 4160.125 868.0361) 
(list 4160.125 868.0464) 
(list 4160.125 868.0567) 
(list 4160.125 868.0669) 
(list 4160.125 868.0772) 
(list 4160.125 868.0875) 
(list 4160.125 868.0978) 
(list 4160.125 868.1081) 
(list 4160.125 868.1183) 
(list 4160.125 868.1286) 
(list 4160.125 868.1389) 
(list 4160.125 868.1492) 
(list 4160.125 868.1594) 
(list 4160.125 868.1697) 
(list 4160.125 868.18) 
(list 4160 868.18)))
(apply 'command (append '("pline") coords '("c")))
(setq tap13 (ssadd (entlast) tap13))
(command "_mirror" (entlast) "" "4160,900" "4160,901" "No")
(setq tap13 (ssadd (entlast) tap13))
(setq coords (list 
(list 4160.4453 867.81) 
(list 4160.4352 867.81) 
(list 4160.4351 867.8203) 
(list 4160.4342 867.8306) 
(list 4160.4325 867.8408) 
(list 4160.4302 867.8511) 
(list 4160.4271 867.8614) 
(list 4160.4235 867.8717) 
(list 4160.4194 867.8819) 
(list 4160.4149 867.8922) 
(list 4160.4102 867.9025) 
(list 4160.4054 867.9128) 
(list 4160.4007 867.9231) 
(list 4160.3962 867.9333) 
(list 4160.3921 867.9436) 
(list 4160.3884 867.9539) 
(list 4160.3854 867.9642) 
(list 4160.3831 867.9744) 
(list 4160.3816 867.9847) 
(list 4160.381 867.995) 
(list 4160.3812 868.0053) 
(list 4160.3824 868.0156) 
(list 4160.3845 868.0258) 
(list 4160.3874 868.0361) 
(list 4160.391 868.0464) 
(list 4160.3953 868.0567) 
(list 4160.4002 868.0669) 
(list 4160.4055 868.0772) 
(list 4160.411 868.0875) 
(list 4160.4166 868.0978) 
(list 4160.4221 868.1081) 
(list 4160.4274 868.1183) 
(list 4160.4322 868.1286) 
(list 4160.4364 868.1389) 
(list 4160.44 868.1492) 
(list 4160.4427 868.1594) 
(list 4160.4445 868.1697) 
(list 4160.4453 868.18) 
(list 4160.4453 868.18)))
(apply 'command (append '("pline") coords '("c")))
(setq tap13 (ssadd (entlast) tap13))
(command "_mirror" (entlast) "" "4160,900" "4160,901" "No")
(setq tap13 (ssadd (entlast) tap13))
(setq coords (list 
(list 4161.112 867.81) 
(list 4160.4453 867.81) 
(list 4160.4453 867.8203) 
(list 4160.4453 867.8306) 
(list 4160.4453 867.8408) 
(list 4160.4453 867.8511) 
(list 4160.4453 867.8614) 
(list 4160.4453 867.8717) 
(list 4160.4453 867.8819) 
(list 4160.4453 867.8922) 
(list 4160.4453 867.9025) 
(list 4160.4453 867.9128) 
(list 4160.4453 867.9231) 
(list 4160.4453 867.9333) 
(list 4160.4453 867.9436) 
(list 4160.4453 867.9539) 
(list 4160.4453 867.9642) 
(list 4160.4453 867.9744) 
(list 4160.4453 867.9847) 
(list 4160.4453 867.995) 
(list 4160.4453 868.0053) 
(list 4160.4453 868.0156) 
(list 4160.4453 868.0258) 
(list 4160.4453 868.0361) 
(list 4160.4453 868.0464) 
(list 4160.4453 868.0567) 
(list 4160.4453 868.0669) 
(list 4160.4453 868.0772) 
(list 4160.4453 868.0875) 
(list 4160.4453 868.0978) 
(list 4160.4453 868.1081) 
(list 4160.4453 868.1183) 
(list 4160.4453 868.1286) 
(list 4160.4453 868.1389) 
(list 4160.4453 868.1492) 
(list 4160.4453 868.1594) 
(list 4160.4453 868.1697) 
(list 4160.4453 868.18) 
(list 4161.112 868.18)))
(apply 'command (append '("pline") coords '("c")))
(setq tap13 (ssadd (entlast) tap13))
(command "_mirror" (entlast) "" "4160,900" "4160,901" "No")
(setq tap13 (ssadd (entlast) tap13))
(setq coords (list 
(list 4160 868.18) 
(list 4160.125 868.18) 
(list 4160.125 868.1903) 
(list 4160.125 868.2006) 
(list 4160.125 868.2108) 
(list 4160.125 868.2211) 
(list 4160.125 868.2314) 
(list 4160.125 868.2417) 
(list 4160.125 868.2519) 
(list 4160.125 868.2622) 
(list 4160.125 868.2725) 
(list 4160.125 868.2828) 
(list 4160.125 868.2931) 
(list 4160.125 868.3033) 
(list 4160.125 868.3136) 
(list 4160.125 868.3239) 
(list 4160.125 868.3342) 
(list 4160.125 868.3444) 
(list 4160.125 868.3547) 
(list 4160.125 868.365) 
(list 4160.125 868.3753) 
(list 4160.125 868.3856) 
(list 4160.125 868.3958) 
(list 4160.125 868.4061) 
(list 4160.125 868.4164) 
(list 4160.125 868.4267) 
(list 4160.125 868.4369) 
(list 4160.125 868.4472) 
(list 4160.125 868.4575) 
(list 4160.125 868.4678) 
(list 4160.125 868.4781) 
(list 4160.125 868.4883) 
(list 4160.125 868.4986) 
(list 4160.125 868.5089) 
(list 4160.125 868.5192) 
(list 4160.125 868.5294) 
(list 4160.125 868.5397) 
(list 4160.125 868.55) 
(list 4160 868.55)))
(apply 'command (append '("pline") coords '("c")))
(setq tap13 (ssadd (entlast) tap13))
(command "_mirror" (entlast) "" "4160,900" "4160,901" "No")
(setq tap13 (ssadd (entlast) tap13))
(setq coords (list 
(list 4160.4553 868.18) 
(list 4160.4453 868.18) 
(list 4160.445 868.1903) 
(list 4160.4438 868.2006) 
(list 4160.4415 868.2108) 
(list 4160.4382 868.2211) 
(list 4160.4341 868.2314) 
(list 4160.4293 868.2417) 
(list 4160.4239 868.2519) 
(list 4160.418 868.2622) 
(list 4160.4118 868.2725) 
(list 4160.4056 868.2828) 
(list 4160.3994 868.2931) 
(list 4160.3936 868.3033) 
(list 4160.3882 868.3136) 
(list 4160.3836 868.3239) 
(list 4160.3797 868.3342) 
(list 4160.3768 868.3444) 
(list 4160.3749 868.3547) 
(list 4160.3741 868.365) 
(list 4160.3745 868.3753) 
(list 4160.376 868.3856) 
(list 4160.3787 868.3958) 
(list 4160.3825 868.4061) 
(list 4160.3872 868.4164) 
(list 4160.3927 868.4267) 
(list 4160.3989 868.4369) 
(list 4160.4056 868.4472) 
(list 4160.4126 868.4575) 
(list 4160.4197 868.4678) 
(list 4160.4266 868.4781) 
(list 4160.4332 868.4883) 
(list 4160.4392 868.4986) 
(list 4160.4445 868.5089) 
(list 4160.4489 868.5192) 
(list 4160.4523 868.5294) 
(list 4160.4544 868.5397) 
(list 4160.4553 868.55) 
(list 4160.4553 868.55)))
(apply 'command (append '("pline") coords '("c")))
(setq tap13 (ssadd (entlast) tap13))
(command "_mirror" (entlast) "" "4160,900" "4160,901" "No")
(setq tap13 (ssadd (entlast) tap13))
(setq coords (list 
(list 4161.112 868.18) 
(list 4160.4553 868.18) 
(list 4160.4553 868.1903) 
(list 4160.4553 868.2006) 
(list 4160.4553 868.2108) 
(list 4160.4553 868.2211) 
(list 4160.4553 868.2314) 
(list 4160.4553 868.2417) 
(list 4160.4553 868.2519) 
(list 4160.4553 868.2622) 
(list 4160.4553 868.2725) 
(list 4160.4553 868.2828) 
(list 4160.4553 868.2931) 
(list 4160.4553 868.3033) 
(list 4160.4553 868.3136) 
(list 4160.4553 868.3239) 
(list 4160.4553 868.3342) 
(list 4160.4553 868.3444) 
(list 4160.4553 868.3547) 
(list 4160.4553 868.365) 
(list 4160.4553 868.3753) 
(list 4160.4553 868.3856) 
(list 4160.4553 868.3958) 
(list 4160.4553 868.4061) 
(list 4160.4553 868.4164) 
(list 4160.4553 868.4267) 
(list 4160.4553 868.4369) 
(list 4160.4553 868.4472) 
(list 4160.4553 868.4575) 
(list 4160.4553 868.4678) 
(list 4160.4553 868.4781) 
(list 4160.4553 868.4883) 
(list 4160.4553 868.4986) 
(list 4160.4553 868.5089) 
(list 4160.4553 868.5192) 
(list 4160.4553 868.5294) 
(list 4160.4553 868.5397) 
(list 4160.4553 868.55) 
(list 4161.112 868.55)))
(apply 'command (append '("pline") coords '("c")))
(setq tap13 (ssadd (entlast) tap13))
(command "_mirror" (entlast) "" "4160,900" "4160,901" "No")
(setq tap13 (ssadd (entlast) tap13))
(setq coords (list 
(list 4160 868.55) 
(list 4160.125 868.55) 
(list 4160.125 868.5603) 
(list 4160.125 868.5706) 
(list 4160.125 868.5808) 
(list 4160.125 868.5911) 
(list 4160.125 868.6014) 
(list 4160.125 868.6117) 
(list 4160.125 868.6219) 
(list 4160.125 868.6322) 
(list 4160.125 868.6425) 
(list 4160.125 868.6528) 
(list 4160.125 868.6631) 
(list 4160.125 868.6733) 
(list 4160.125 868.6836) 
(list 4160.125 868.6939) 
(list 4160.125 868.7042) 
(list 4160.125 868.7144) 
(list 4160.125 868.7247) 
(list 4160.125 868.735) 
(list 4160.125 868.7453) 
(list 4160.125 868.7556) 
(list 4160.125 868.7658) 
(list 4160.125 868.7761) 
(list 4160.125 868.7864) 
(list 4160.125 868.7967) 
(list 4160.125 868.8069) 
(list 4160.125 868.8172) 
(list 4160.125 868.8275) 
(list 4160.125 868.8378) 
(list 4160.125 868.8481) 
(list 4160.125 868.8583) 
(list 4160.125 868.8686) 
(list 4160.125 868.8789) 
(list 4160.125 868.8892) 
(list 4160.125 868.8994) 
(list 4160.125 868.9097) 
(list 4160.125 868.92) 
(list 4160 868.92)))
(apply 'command (append '("pline") coords '("c")))
(setq tap13 (ssadd (entlast) tap13))
(command "_mirror" (entlast) "" "4160,900" "4160,901" "No")
(setq tap13 (ssadd (entlast) tap13))
(setq coords (list 
(list 4160.4654 868.55) 
(list 4160.4553 868.55) 
(list 4160.455 868.5603) 
(list 4160.4533 868.5706) 
(list 4160.4504 868.5808) 
(list 4160.4463 868.5911) 
(list 4160.4412 868.6014) 
(list 4160.4351 868.6117) 
(list 4160.4284 868.6219) 
(list 4160.421 868.6322) 
(list 4160.4134 868.6425) 
(list 4160.4057 868.6528) 
(list 4160.3981 868.6631) 
(list 4160.391 868.6733) 
(list 4160.3844 868.6836) 
(list 4160.3787 868.6939) 
(list 4160.374 868.7042) 
(list 4160.3704 868.7144) 
(list 4160.3681 868.7247) 
(list 4160.3672 868.735) 
(list 4160.3678 868.7453) 
(list 4160.3697 868.7556) 
(list 4160.373 868.7658) 
(list 4160.3776 868.7761) 
(list 4160.3833 868.7864) 
(list 4160.3901 868.7967) 
(list 4160.3976 868.8069) 
(list 4160.4057 868.8172) 
(list 4160.4142 868.8275) 
(list 4160.4227 868.8378) 
(list 4160.4311 868.8481) 
(list 4160.439 868.8583) 
(list 4160.4463 868.8686) 
(list 4160.4526 868.8789) 
(list 4160.4578 868.8892) 
(list 4160.4618 868.8994) 
(list 4160.4644 868.9097) 
(list 4160.4654 868.92) 
(list 4160.4654 868.92)))
(apply 'command (append '("pline") coords '("c")))
(setq tap13 (ssadd (entlast) tap13))
(command "_mirror" (entlast) "" "4160,900" "4160,901" "No")
(setq tap13 (ssadd (entlast) tap13))
(setq coords (list 
(list 4161.112 868.55) 
(list 4160.4654 868.55) 
(list 4160.4654 868.5603) 
(list 4160.4654 868.5706) 
(list 4160.4654 868.5808) 
(list 4160.4654 868.5911) 
(list 4160.4654 868.6014) 
(list 4160.4654 868.6117) 
(list 4160.4654 868.6219) 
(list 4160.4654 868.6322) 
(list 4160.4654 868.6425) 
(list 4160.4654 868.6528) 
(list 4160.4654 868.6631) 
(list 4160.4654 868.6733) 
(list 4160.4654 868.6836) 
(list 4160.4654 868.6939) 
(list 4160.4654 868.7042) 
(list 4160.4654 868.7144) 
(list 4160.4654 868.7247) 
(list 4160.4654 868.735) 
(list 4160.4654 868.7453) 
(list 4160.4654 868.7556) 
(list 4160.4654 868.7658) 
(list 4160.4654 868.7761) 
(list 4160.4654 868.7864) 
(list 4160.4654 868.7967) 
(list 4160.4654 868.8069) 
(list 4160.4654 868.8172) 
(list 4160.4654 868.8275) 
(list 4160.4654 868.8378) 
(list 4160.4654 868.8481) 
(list 4160.4654 868.8583) 
(list 4160.4654 868.8686) 
(list 4160.4654 868.8789) 
(list 4160.4654 868.8892) 
(list 4160.4654 868.8994) 
(list 4160.4654 868.9097) 
(list 4160.4654 868.92) 
(list 4161.112 868.92)))
(apply 'command (append '("pline") coords '("c")))
(setq tap13 (ssadd (entlast) tap13))
(command "_mirror" (entlast) "" "4160,900" "4160,901" "No")
(setq tap13 (ssadd (entlast) tap13))
(setq coords (list 
(list 4160 868.92) 
(list 4160.125 868.92) 
(list 4160.125 868.9303) 
(list 4160.125 868.9406) 
(list 4160.125 868.9508) 
(list 4160.125 868.9611) 
(list 4160.125 868.9714) 
(list 4160.125 868.9817) 
(list 4160.125 868.9919) 
(list 4160.125 869.0022) 
(list 4160.125 869.0125) 
(list 4160.125 869.0228) 
(list 4160.125 869.0331) 
(list 4160.125 869.0433) 
(list 4160.125 869.0536) 
(list 4160.125 869.0639) 
(list 4160.125 869.0742) 
(list 4160.125 869.0844) 
(list 4160.125 869.0947) 
(list 4160.125 869.105) 
(list 4160.125 869.1153) 
(list 4160.125 869.1256) 
(list 4160.125 869.1358) 
(list 4160.125 869.1461) 
(list 4160.125 869.1564) 
(list 4160.125 869.1667) 
(list 4160.125 869.1769) 
(list 4160.125 869.1872) 
(list 4160.125 869.1975) 
(list 4160.125 869.2078) 
(list 4160.125 869.2181) 
(list 4160.125 869.2283) 
(list 4160.125 869.2386) 
(list 4160.125 869.2489) 
(list 4160.125 869.2592) 
(list 4160.125 869.2694) 
(list 4160.125 869.2797) 
(list 4160.125 869.29) 
(list 4160 869.29)))
(apply 'command (append '("pline") coords '("c")))
(setq tap13 (ssadd (entlast) tap13))
(command "_mirror" (entlast) "" "4160,900" "4160,901" "No")
(setq tap13 (ssadd (entlast) tap13))
(setq coords (list 
(list 4160.4755 868.92) 
(list 4160.4654 868.92) 
(list 4160.4649 868.9303) 
(list 4160.4629 868.9406) 
(list 4160.4593 868.9508) 
(list 4160.4544 868.9611) 
(list 4160.4482 868.9714) 
(list 4160.441 868.9817) 
(list 4160.4328 868.9919) 
(list 4160.4241 869.0022) 
(list 4160.415 869.0125) 
(list 4160.4058 869.0228) 
(list 4160.3968 869.0331) 
(list 4160.3883 869.0433) 
(list 4160.3806 869.0536) 
(list 4160.3738 869.0639) 
(list 4160.3682 869.0742) 
(list 4160.364 869.0844) 
(list 4160.3614 869.0947) 
(list 4160.3604 869.105) 
(list 4160.361 869.1153) 
(list 4160.3633 869.1256) 
(list 4160.3673 869.1358) 
(list 4160.3727 869.1461) 
(list 4160.3795 869.1564) 
(list 4160.3874 869.1667) 
(list 4160.3963 869.1769) 
(list 4160.4059 869.1872) 
(list 4160.4158 869.1975) 
(list 4160.4258 869.2078) 
(list 4160.4356 869.2181) 
(list 4160.4449 869.2283) 
(list 4160.4533 869.2386) 
(list 4160.4607 869.2489) 
(list 4160.4668 869.2592) 
(list 4160.4714 869.2694) 
(list 4160.4743 869.2797) 
(list 4160.4755 869.29) 
(list 4160.4755 869.29)))
(apply 'command (append '("pline") coords '("c")))
(setq tap13 (ssadd (entlast) tap13))
(command "_mirror" (entlast) "" "4160,900" "4160,901" "No")
(setq tap13 (ssadd (entlast) tap13))
(setq coords (list 
(list 4161.112 868.92) 
(list 4160.4755 868.92) 
(list 4160.4755 868.9303) 
(list 4160.4755 868.9406) 
(list 4160.4755 868.9508) 
(list 4160.4755 868.9611) 
(list 4160.4755 868.9714) 
(list 4160.4755 868.9817) 
(list 4160.4755 868.9919) 
(list 4160.4755 869.0022) 
(list 4160.4755 869.0125) 
(list 4160.4755 869.0228) 
(list 4160.4755 869.0331) 
(list 4160.4755 869.0433) 
(list 4160.4755 869.0536) 
(list 4160.4755 869.0639) 
(list 4160.4755 869.0742) 
(list 4160.4755 869.0844) 
(list 4160.4755 869.0947) 
(list 4160.4755 869.105) 
(list 4160.4755 869.1153) 
(list 4160.4755 869.1256) 
(list 4160.4755 869.1358) 
(list 4160.4755 869.1461) 
(list 4160.4755 869.1564) 
(list 4160.4755 869.1667) 
(list 4160.4755 869.1769) 
(list 4160.4755 869.1872) 
(list 4160.4755 869.1975) 
(list 4160.4755 869.2078) 
(list 4160.4755 869.2181) 
(list 4160.4755 869.2283) 
(list 4160.4755 869.2386) 
(list 4160.4755 869.2489) 
(list 4160.4755 869.2592) 
(list 4160.4755 869.2694) 
(list 4160.4755 869.2797) 
(list 4160.4755 869.29) 
(list 4161.112 869.29)))
(apply 'command (append '("pline") coords '("c")))
(setq tap13 (ssadd (entlast) tap13))
(command "_mirror" (entlast) "" "4160,900" "4160,901" "No")
(setq tap13 (ssadd (entlast) tap13))
(setq coords (list 
(list 4160 869.29) 
(list 4160.125 869.29) 
(list 4160.125 869.3003) 
(list 4160.125 869.3106) 
(list 4160.125 869.3208) 
(list 4160.125 869.3311) 
(list 4160.125 869.3414) 
(list 4160.125 869.3517) 
(list 4160.125 869.3619) 
(list 4160.125 869.3722) 
(list 4160.125 869.3825) 
(list 4160.125 869.3928) 
(list 4160.125 869.4031) 
(list 4160.125 869.4133) 
(list 4160.125 869.4236) 
(list 4160.125 869.4339) 
(list 4160.125 869.4442) 
(list 4160.125 869.4544) 
(list 4160.125 869.4647) 
(list 4160.125 869.475) 
(list 4160.125 869.4853) 
(list 4160.125 869.4956) 
(list 4160.125 869.5058) 
(list 4160.125 869.5161) 
(list 4160.125 869.5264) 
(list 4160.125 869.5367) 
(list 4160.125 869.5469) 
(list 4160.125 869.5572) 
(list 4160.125 869.5675) 
(list 4160.125 869.5778) 
(list 4160.125 869.5881) 
(list 4160.125 869.5983) 
(list 4160.125 869.6086) 
(list 4160.125 869.6189) 
(list 4160.125 869.6292) 
(list 4160.125 869.6394) 
(list 4160.125 869.6497) 
(list 4160.125 869.66) 
(list 4160 869.66)))
(apply 'command (append '("pline") coords '("c")))
(setq tap13 (ssadd (entlast) tap13))
(command "_mirror" (entlast) "" "4160,900" "4160,901" "No")
(setq tap13 (ssadd (entlast) tap13))
(setq coords (list 
(list 4160.4855 869.29) 
(list 4160.4755 869.29) 
(list 4160.4748 869.3003) 
(list 4160.4724 869.3106) 
(list 4160.4683 869.3208) 
(list 4160.4625 869.3311) 
(list 4160.4553 869.3414) 
(list 4160.4468 869.3517) 
(list 4160.4373 869.3619) 
(list 4160.4272 869.3722) 
(list 4160.4166 869.3825) 
(list 4160.4059 869.3928) 
(list 4160.3955 869.4031) 
(list 4160.3857 869.4133) 
(list 4160.3767 869.4236) 
(list 4160.3689 869.4339) 
(list 4160.3625 869.4442) 
(list 4160.3577 869.4544) 
(list 4160.3547 869.4647) 
(list 4160.3535 869.475) 
(list 4160.3543 869.4853) 
(list 4160.357 869.4956) 
(list 4160.3615 869.5058) 
(list 4160.3678 869.5161) 
(list 4160.3756 869.5264) 
(list 4160.3848 869.5367) 
(list 4160.395 869.5469) 
(list 4160.406 869.5572) 
(list 4160.4174 869.5675) 
(list 4160.4289 869.5778) 
(list 4160.4401 869.5881) 
(list 4160.4507 869.5983) 
(list 4160.4604 869.6086) 
(list 4160.4688 869.6189) 
(list 4160.4757 869.6292) 
(list 4160.4809 869.6394) 
(list 4160.4842 869.6497) 
(list 4160.4855 869.66) 
(list 4160.4855 869.66)))
(apply 'command (append '("pline") coords '("c")))
(setq tap13 (ssadd (entlast) tap13))
(command "_mirror" (entlast) "" "4160,900" "4160,901" "No")
(setq tap13 (ssadd (entlast) tap13))
(setq coords (list 
(list 4161.112 869.29) 
(list 4160.4855 869.29) 
(list 4160.4855 869.3003) 
(list 4160.4855 869.3106) 
(list 4160.4855 869.3208) 
(list 4160.4855 869.3311) 
(list 4160.4855 869.3414) 
(list 4160.4855 869.3517) 
(list 4160.4855 869.3619) 
(list 4160.4855 869.3722) 
(list 4160.4855 869.3825) 
(list 4160.4855 869.3928) 
(list 4160.4855 869.4031) 
(list 4160.4855 869.4133) 
(list 4160.4855 869.4236) 
(list 4160.4855 869.4339) 
(list 4160.4855 869.4442) 
(list 4160.4855 869.4544) 
(list 4160.4855 869.4647) 
(list 4160.4855 869.475) 
(list 4160.4855 869.4853) 
(list 4160.4855 869.4956) 
(list 4160.4855 869.5058) 
(list 4160.4855 869.5161) 
(list 4160.4855 869.5264) 
(list 4160.4855 869.5367) 
(list 4160.4855 869.5469) 
(list 4160.4855 869.5572) 
(list 4160.4855 869.5675) 
(list 4160.4855 869.5778) 
(list 4160.4855 869.5881) 
(list 4160.4855 869.5983) 
(list 4160.4855 869.6086) 
(list 4160.4855 869.6189) 
(list 4160.4855 869.6292) 
(list 4160.4855 869.6394) 
(list 4160.4855 869.6497) 
(list 4160.4855 869.66) 
(list 4161.112 869.66)))
(apply 'command (append '("pline") coords '("c")))
(setq tap13 (ssadd (entlast) tap13))
(command "_mirror" (entlast) "" "4160,900" "4160,901" "No")
(setq tap13 (ssadd (entlast) tap13))
(setq coords (list 
(list 4160 869.66) 
(list 4160.125 869.66) 
(list 4160.125 869.6703) 
(list 4160.125 869.6806) 
(list 4160.125 869.6908) 
(list 4160.125 869.7011) 
(list 4160.125 869.7114) 
(list 4160.125 869.7217) 
(list 4160.125 869.7319) 
(list 4160.125 869.7422) 
(list 4160.125 869.7525) 
(list 4160.125 869.7628) 
(list 4160.125 869.7731) 
(list 4160.125 869.7833) 
(list 4160.125 869.7936) 
(list 4160.125 869.8039) 
(list 4160.125 869.8142) 
(list 4160.125 869.8244) 
(list 4160.125 869.8347) 
(list 4160.125 869.845) 
(list 4160.125 869.8553) 
(list 4160.125 869.8656) 
(list 4160.125 869.8758) 
(list 4160.125 869.8861) 
(list 4160.125 869.8964) 
(list 4160.125 869.9067) 
(list 4160.125 869.9169) 
(list 4160.125 869.9272) 
(list 4160.125 869.9375) 
(list 4160.125 869.9478) 
(list 4160.125 869.9581) 
(list 4160.125 869.9683) 
(list 4160.125 869.9786) 
(list 4160.125 869.9889) 
(list 4160.125 869.9992) 
(list 4160.125 870.0094) 
(list 4160.125 870.0197) 
(list 4160.125 870.03) 
(list 4160 870.03)))
(apply 'command (append '("pline") coords '("c")))
(setq tap13 (ssadd (entlast) tap13))
(command "_mirror" (entlast) "" "4160,900" "4160,901" "No")
(setq tap13 (ssadd (entlast) tap13))
(setq coords (list 
(list 4160.4956 869.66) 
(list 4160.4855 869.66) 
(list 4160.4848 869.6703) 
(list 4160.482 869.6806) 
(list 4160.4772 869.6908) 
(list 4160.4706 869.7011) 
(list 4160.4623 869.7114) 
(list 4160.4526 869.7217) 
(list 4160.4418 869.7319) 
(list 4160.4302 869.7422) 
(list 4160.4182 869.7525) 
(list 4160.4061 869.7628) 
(list 4160.3942 869.7731) 
(list 4160.3831 869.7833) 
(list 4160.3729 869.7936) 
(list 4160.364 869.8039) 
(list 4160.3568 869.8142) 
(list 4160.3513 869.8244) 
(list 4160.3479 869.8347) 
(list 4160.3466 869.845) 
(list 4160.3475 869.8553) 
(list 4160.3506 869.8656) 
(list 4160.3558 869.8758) 
(list 4160.3629 869.8861) 
(list 4160.3718 869.8964) 
(list 4160.3822 869.9067) 
(list 4160.3937 869.9169) 
(list 4160.4061 869.9272) 
(list 4160.419 869.9375) 
(list 4160.432 869.9478) 
(list 4160.4446 869.9581) 
(list 4160.4565 869.9683) 
(list 4160.4674 869.9786) 
(list 4160.4769 869.9889) 
(list 4160.4846 869.9992) 
(list 4160.4905 870.0094) 
(list 4160.4942 870.0197) 
(list 4160.4956 870.03) 
(list 4160.4956 870.03)))
(apply 'command (append '("pline") coords '("c")))
(setq tap13 (ssadd (entlast) tap13))
(command "_mirror" (entlast) "" "4160,900" "4160,901" "No")
(setq tap13 (ssadd (entlast) tap13))
(setq coords (list 
(list 4161.112 869.66) 
(list 4160.4956 869.66) 
(list 4160.4956 869.6703) 
(list 4160.4956 869.6806) 
(list 4160.4956 869.6908) 
(list 4160.4956 869.7011) 
(list 4160.4956 869.7114) 
(list 4160.4956 869.7217) 
(list 4160.4956 869.7319) 
(list 4160.4956 869.7422) 
(list 4160.4956 869.7525) 
(list 4160.4956 869.7628) 
(list 4160.4956 869.7731) 
(list 4160.4956 869.7833) 
(list 4160.4956 869.7936) 
(list 4160.4956 869.8039) 
(list 4160.4956 869.8142) 
(list 4160.4956 869.8244) 
(list 4160.4956 869.8347) 
(list 4160.4956 869.845) 
(list 4160.4956 869.8553) 
(list 4160.4956 869.8656) 
(list 4160.4956 869.8758) 
(list 4160.4956 869.8861) 
(list 4160.4956 869.8964) 
(list 4160.4956 869.9067) 
(list 4160.4956 869.9169) 
(list 4160.4956 869.9272) 
(list 4160.4956 869.9375) 
(list 4160.4956 869.9478) 
(list 4160.4956 869.9581) 
(list 4160.4956 869.9683) 
(list 4160.4956 869.9786) 
(list 4160.4956 869.9889) 
(list 4160.4956 869.9992) 
(list 4160.4956 870.0094) 
(list 4160.4956 870.0197) 
(list 4160.4956 870.03) 
(list 4161.112 870.03)))
(apply 'command (append '("pline") coords '("c")))
(setq tap13 (ssadd (entlast) tap13))
(command "_mirror" (entlast) "" "4160,900" "4160,901" "No")
(setq tap13 (ssadd (entlast) tap13))
(setq coords (list 
(list 4160 870.03) 
(list 4160.125 870.03) 
(list 4160.125 870.0403) 
(list 4160.125 870.0506) 
(list 4160.125 870.0608) 
(list 4160.125 870.0711) 
(list 4160.125 870.0814) 
(list 4160.125 870.0917) 
(list 4160.125 870.1019) 
(list 4160.125 870.1122) 
(list 4160.125 870.1225) 
(list 4160.125 870.1328) 
(list 4160.125 870.1431) 
(list 4160.125 870.1533) 
(list 4160.125 870.1636) 
(list 4160.125 870.1739) 
(list 4160.125 870.1842) 
(list 4160.125 870.1944) 
(list 4160.125 870.2047) 
(list 4160.125 870.215) 
(list 4160.125 870.2253) 
(list 4160.125 870.2356) 
(list 4160.125 870.2458) 
(list 4160.125 870.2561) 
(list 4160.125 870.2664) 
(list 4160.125 870.2767) 
(list 4160.125 870.2869) 
(list 4160.125 870.2972) 
(list 4160.125 870.3075) 
(list 4160.125 870.3178) 
(list 4160.125 870.3281) 
(list 4160.125 870.3383) 
(list 4160.125 870.3486) 
(list 4160.125 870.3589) 
(list 4160.125 870.3692) 
(list 4160.125 870.3794) 
(list 4160.125 870.3897) 
(list 4160.125 870.4) 
(list 4160 870.4)))
(apply 'command (append '("pline") coords '("c")))
(setq tap13 (ssadd (entlast) tap13))
(command "_mirror" (entlast) "" "4160,900" "4160,901" "No")
(setq tap13 (ssadd (entlast) tap13))
(setq coords (list 
(list 4160.5057 870.03) 
(list 4160.4956 870.03) 
(list 4160.4947 870.0403) 
(list 4160.4915 870.0506) 
(list 4160.4861 870.0608) 
(list 4160.4787 870.0711) 
(list 4160.4694 870.0814) 
(list 4160.4585 870.0917) 
(list 4160.4463 870.1019) 
(list 4160.4333 870.1122) 
(list 4160.4198 870.1225) 
(list 4160.4062 870.1328) 
(list 4160.3929 870.1431) 
(list 4160.3804 870.1533) 
(list 4160.369 870.1636) 
(list 4160.3591 870.1739) 
(list 4160.351 870.1842) 
(list 4160.345 870.1944) 
(list 4160.3412 870.2047) 
(list 4160.3398 870.215) 
(list 4160.3408 870.2253) 
(list 4160.3443 870.2356) 
(list 4160.3501 870.2458) 
(list 4160.358 870.2561) 
(list 4160.368 870.2664) 
(list 4160.3795 870.2767) 
(list 4160.3924 870.2869) 
(list 4160.4063 870.2972) 
(list 4160.4206 870.3075) 
(list 4160.435 870.3178) 
(list 4160.4491 870.3281) 
(list 4160.4624 870.3383) 
(list 4160.4744 870.3486) 
(list 4160.485 870.3589) 
(list 4160.4936 870.3692) 
(list 4160.5 870.3794) 
(list 4160.5041 870.3897) 
(list 4160.5057 870.4) 
(list 4160.5057 870.4)))
(apply 'command (append '("pline") coords '("c")))
(setq tap13 (ssadd (entlast) tap13))
(command "_mirror" (entlast) "" "4160,900" "4160,901" "No")
(setq tap13 (ssadd (entlast) tap13))
(setq coords (list 
(list 4161.112 870.03) 
(list 4160.5057 870.03) 
(list 4160.5057 870.0403) 
(list 4160.5057 870.0506) 
(list 4160.5057 870.0608) 
(list 4160.5057 870.0711) 
(list 4160.5057 870.0814) 
(list 4160.5057 870.0917) 
(list 4160.5057 870.1019) 
(list 4160.5057 870.1122) 
(list 4160.5057 870.1225) 
(list 4160.5057 870.1328) 
(list 4160.5057 870.1431) 
(list 4160.5057 870.1533) 
(list 4160.5057 870.1636) 
(list 4160.5057 870.1739) 
(list 4160.5057 870.1842) 
(list 4160.5057 870.1944) 
(list 4160.5057 870.2047) 
(list 4160.5057 870.215) 
(list 4160.5057 870.2253) 
(list 4160.5057 870.2356) 
(list 4160.5057 870.2458) 
(list 4160.5057 870.2561) 
(list 4160.5057 870.2664) 
(list 4160.5057 870.2767) 
(list 4160.5057 870.2869) 
(list 4160.5057 870.2972) 
(list 4160.5057 870.3075) 
(list 4160.5057 870.3178) 
(list 4160.5057 870.3281) 
(list 4160.5057 870.3383) 
(list 4160.5057 870.3486) 
(list 4160.5057 870.3589) 
(list 4160.5057 870.3692) 
(list 4160.5057 870.3794) 
(list 4160.5057 870.3897) 
(list 4160.5057 870.4) 
(list 4161.112 870.4)))
(apply 'command (append '("pline") coords '("c")))
(setq tap13 (ssadd (entlast) tap13))
(command "_mirror" (entlast) "" "4160,900" "4160,901" "No")
(setq tap13 (ssadd (entlast) tap13))
(setq coords (list 
(list 4160 870.4) 
(list 4160.125 870.4) 
(list 4160.125 870.4103) 
(list 4160.125 870.4206) 
(list 4160.125 870.4308) 
(list 4160.125 870.4411) 
(list 4160.125 870.4514) 
(list 4160.125 870.4617) 
(list 4160.125 870.4719) 
(list 4160.125 870.4822) 
(list 4160.125 870.4925) 
(list 4160.125 870.5028) 
(list 4160.125 870.5131) 
(list 4160.125 870.5233) 
(list 4160.125 870.5336) 
(list 4160.125 870.5439) 
(list 4160.125 870.5542) 
(list 4160.125 870.5644) 
(list 4160.125 870.5747) 
(list 4160.125 870.585) 
(list 4160.125 870.5953) 
(list 4160.125 870.6056) 
(list 4160.125 870.6158) 
(list 4160.125 870.6261) 
(list 4160.125 870.6364) 
(list 4160.125 870.6467) 
(list 4160.125 870.6569) 
(list 4160.125 870.6672) 
(list 4160.125 870.6775) 
(list 4160.125 870.6878) 
(list 4160.125 870.6981) 
(list 4160.125 870.7083) 
(list 4160.125 870.7186) 
(list 4160.125 870.7289) 
(list 4160.125 870.7392) 
(list 4160.125 870.7494) 
(list 4160.125 870.7597) 
(list 4160.125 870.77) 
(list 4160 870.77)))
(apply 'command (append '("pline") coords '("c")))
(setq tap13 (ssadd (entlast) tap13))
(command "_mirror" (entlast) "" "4160,900" "4160,901" "No")
(setq tap13 (ssadd (entlast) tap13))
(setq coords (list 
(list 4160.5157 870.4) 
(list 4160.5057 870.4) 
(list 4160.5047 870.4103) 
(list 4160.5011 870.4206) 
(list 4160.4951 870.4308) 
(list 4160.4868 870.4411) 
(list 4160.4764 870.4514) 
(list 4160.4643 870.4617) 
(list 4160.4508 870.4719) 
(list 4160.4364 870.4822) 
(list 4160.4214 870.4925) 
(list 4160.4063 870.5028) 
(list 4160.3916 870.5131) 
(list 4160.3778 870.5233) 
(list 4160.3652 870.5336) 
(list 4160.3542 870.5439) 
(list 4160.3453 870.5542) 
(list 4160.3386 870.5644) 
(list 4160.3344 870.5747) 
(list 4160.3329 870.585) 
(list 4160.3341 870.5953) 
(list 4160.3379 870.6056) 
(list 4160.3443 870.6158) 
(list 4160.3532 870.6261) 
(list 4160.3641 870.6364) 
(list 4160.3769 870.6467) 
(list 4160.3911 870.6569) 
(list 4160.4064 870.6672) 
(list 4160.4222 870.6775) 
(list 4160.4381 870.6878) 
(list 4160.4536 870.6981) 
(list 4160.4682 870.7083) 
(list 4160.4815 870.7186) 
(list 4160.493 870.7289) 
(list 4160.5025 870.7392) 
(list 4160.5096 870.7494) 
(list 4160.514 870.7597) 
(list 4160.5157 870.77) 
(list 4160.5157 870.77)))
(apply 'command (append '("pline") coords '("c")))
(setq tap13 (ssadd (entlast) tap13))
(command "_mirror" (entlast) "" "4160,900" "4160,901" "No")
(setq tap13 (ssadd (entlast) tap13))
(setq coords (list 
(list 4161.112 870.4) 
(list 4160.5157 870.4) 
(list 4160.5157 870.4103) 
(list 4160.5157 870.4206) 
(list 4160.5157 870.4308) 
(list 4160.5157 870.4411) 
(list 4160.5157 870.4514) 
(list 4160.5157 870.4617) 
(list 4160.5157 870.4719) 
(list 4160.5157 870.4822) 
(list 4160.5157 870.4925) 
(list 4160.5157 870.5028) 
(list 4160.5157 870.5131) 
(list 4160.5157 870.5233) 
(list 4160.5157 870.5336) 
(list 4160.5157 870.5439) 
(list 4160.5157 870.5542) 
(list 4160.5157 870.5644) 
(list 4160.5157 870.5747) 
(list 4160.5157 870.585) 
(list 4160.5157 870.5953) 
(list 4160.5157 870.6056) 
(list 4160.5157 870.6158) 
(list 4160.5157 870.6261) 
(list 4160.5157 870.6364) 
(list 4160.5157 870.6467) 
(list 4160.5157 870.6569) 
(list 4160.5157 870.6672) 
(list 4160.5157 870.6775) 
(list 4160.5157 870.6878) 
(list 4160.5157 870.6981) 
(list 4160.5157 870.7083) 
(list 4160.5157 870.7186) 
(list 4160.5157 870.7289) 
(list 4160.5157 870.7392) 
(list 4160.5157 870.7494) 
(list 4160.5157 870.7597) 
(list 4160.5157 870.77) 
(list 4161.112 870.77)))
(apply 'command (append '("pline") coords '("c")))
(setq tap13 (ssadd (entlast) tap13))
(command "_mirror" (entlast) "" "4160,900" "4160,901" "No")
(setq tap13 (ssadd (entlast) tap13))
(setq coords (list 
(list 4160 870.77) 
(list 4160.125 870.77) 
(list 4160.125 870.7803) 
(list 4160.125 870.7906) 
(list 4160.125 870.8008) 
(list 4160.125 870.8111) 
(list 4160.125 870.8214) 
(list 4160.125 870.8317) 
(list 4160.125 870.8419) 
(list 4160.125 870.8522) 
(list 4160.125 870.8625) 
(list 4160.125 870.8728) 
(list 4160.125 870.8831) 
(list 4160.125 870.8933) 
(list 4160.125 870.9036) 
(list 4160.125 870.9139) 
(list 4160.125 870.9242) 
(list 4160.125 870.9344) 
(list 4160.125 870.9447) 
(list 4160.125 870.955) 
(list 4160.125 870.9653) 
(list 4160.125 870.9756) 
(list 4160.125 870.9858) 
(list 4160.125 870.9961) 
(list 4160.125 871.0064) 
(list 4160.125 871.0167) 
(list 4160.125 871.0269) 
(list 4160.125 871.0372) 
(list 4160.125 871.0475) 
(list 4160.125 871.0578) 
(list 4160.125 871.0681) 
(list 4160.125 871.0783) 
(list 4160.125 871.0886) 
(list 4160.125 871.0989) 
(list 4160.125 871.1092) 
(list 4160.125 871.1194) 
(list 4160.125 871.1297) 
(list 4160.125 871.14) 
(list 4160 871.14)))
(apply 'command (append '("pline") coords '("c")))
(setq tap13 (ssadd (entlast) tap13))
(command "_mirror" (entlast) "" "4160,900" "4160,901" "No")
(setq tap13 (ssadd (entlast) tap13))
(setq coords (list 
(list 4160.5258 870.77) 
(list 4160.5157 870.77) 
(list 4160.5146 870.7803) 
(list 4160.5106 870.7906) 
(list 4160.504 870.8008) 
(list 4160.4948 870.8111) 
(list 4160.4834 870.8214) 
(list 4160.4701 870.8317) 
(list 4160.4553 870.8419) 
(list 4160.4395 870.8522) 
(list 4160.423 870.8625) 
(list 4160.4065 870.8728) 
(list 4160.3903 870.8831) 
(list 4160.3752 870.8933) 
(list 4160.3613 870.9036) 
(list 4160.3494 870.9139) 
(list 4160.3396 870.9242) 
(list 4160.3323 870.9344) 
(list 4160.3277 870.9447) 
(list 4160.326 870.955) 
(list 4160.3273 870.9653) 
(list 4160.3316 870.9756) 
(list 4160.3386 870.9858) 
(list 4160.3483 870.9961) 
(list 4160.3603 871.0064) 
(list 4160.3743 871.0167) 
(list 4160.3898 871.0269) 
(list 4160.4065 871.0372) 
(list 4160.4238 871.0475) 
(list 4160.4412 871.0578) 
(list 4160.4581 871.0681) 
(list 4160.474 871.0783) 
(list 4160.4885 871.0886) 
(list 4160.5011 871.0989) 
(list 4160.5114 871.1092) 
(list 4160.5191 871.1194) 
(list 4160.524 871.1297) 
(list 4160.5258 871.14) 
(list 4160.5258 871.14)))
(apply 'command (append '("pline") coords '("c")))
(setq tap13 (ssadd (entlast) tap13))
(command "_mirror" (entlast) "" "4160,900" "4160,901" "No")
(setq tap13 (ssadd (entlast) tap13))
(setq coords (list 
(list 4161.112 870.77) 
(list 4160.5258 870.77) 
(list 4160.5258 870.7803) 
(list 4160.5258 870.7906) 
(list 4160.5258 870.8008) 
(list 4160.5258 870.8111) 
(list 4160.5258 870.8214) 
(list 4160.5258 870.8317) 
(list 4160.5258 870.8419) 
(list 4160.5258 870.8522) 
(list 4160.5258 870.8625) 
(list 4160.5258 870.8728) 
(list 4160.5258 870.8831) 
(list 4160.5258 870.8933) 
(list 4160.5258 870.9036) 
(list 4160.5258 870.9139) 
(list 4160.5258 870.9242) 
(list 4160.5258 870.9344) 
(list 4160.5258 870.9447) 
(list 4160.5258 870.955) 
(list 4160.5258 870.9653) 
(list 4160.5258 870.9756) 
(list 4160.5258 870.9858) 
(list 4160.5258 870.9961) 
(list 4160.5258 871.0064) 
(list 4160.5258 871.0167) 
(list 4160.5258 871.0269) 
(list 4160.5258 871.0372) 
(list 4160.5258 871.0475) 
(list 4160.5258 871.0578) 
(list 4160.5258 871.0681) 
(list 4160.5258 871.0783) 
(list 4160.5258 871.0886) 
(list 4160.5258 871.0989) 
(list 4160.5258 871.1092) 
(list 4160.5258 871.1194) 
(list 4160.5258 871.1297) 
(list 4160.5258 871.14) 
(list 4161.112 871.14)))
(apply 'command (append '("pline") coords '("c")))
(setq tap13 (ssadd (entlast) tap13))
(command "_mirror" (entlast) "" "4160,900" "4160,901" "No")
(setq tap13 (ssadd (entlast) tap13))
(setq coords (list 
(list 4160 871.14) 
(list 4160.125 871.14) 
(list 4160.125 871.1503) 
(list 4160.125 871.1606) 
(list 4160.125 871.1708) 
(list 4160.125 871.1811) 
(list 4160.125 871.1914) 
(list 4160.125 871.2017) 
(list 4160.125 871.2119) 
(list 4160.125 871.2222) 
(list 4160.125 871.2325) 
(list 4160.125 871.2428) 
(list 4160.125 871.2531) 
(list 4160.125 871.2633) 
(list 4160.125 871.2736) 
(list 4160.125 871.2839) 
(list 4160.125 871.2942) 
(list 4160.125 871.3044) 
(list 4160.125 871.3147) 
(list 4160.125 871.325) 
(list 4160.125 871.3353) 
(list 4160.125 871.3456) 
(list 4160.125 871.3558) 
(list 4160.125 871.3661) 
(list 4160.125 871.3764) 
(list 4160.125 871.3867) 
(list 4160.125 871.3969) 
(list 4160.125 871.4072) 
(list 4160.125 871.4175) 
(list 4160.125 871.4278) 
(list 4160.125 871.4381) 
(list 4160.125 871.4483) 
(list 4160.125 871.4586) 
(list 4160.125 871.4689) 
(list 4160.125 871.4792) 
(list 4160.125 871.4894) 
(list 4160.125 871.4997) 
(list 4160.125 871.51) 
(list 4160 871.51)))
(apply 'command (append '("pline") coords '("c")))
(setq tap13 (ssadd (entlast) tap13))
(command "_mirror" (entlast) "" "4160,900" "4160,901" "No")
(setq tap13 (ssadd (entlast) tap13))
(setq coords (list 
(list 4160.5359 871.14) 
(list 4160.5258 871.14) 
(list 4160.5245 871.1503) 
(list 4160.5202 871.1606) 
(list 4160.5129 871.1708) 
(list 4160.5029 871.1811) 
(list 4160.4905 871.1914) 
(list 4160.476 871.2017) 
(list 4160.4598 871.2119) 
(list 4160.4425 871.2222) 
(list 4160.4246 871.2325) 
(list 4160.4066 871.2428) 
(list 4160.3891 871.2531) 
(list 4160.3725 871.2633) 
(list 4160.3575 871.2736) 
(list 4160.3445 871.2839) 
(list 4160.3338 871.2942) 
(list 4160.3259 871.3044) 
(list 4160.321 871.3147) 
(list 4160.3192 871.325) 
(list 4160.3206 871.3353) 
(list 4160.3252 871.3456) 
(list 4160.3329 871.3558) 
(list 4160.3434 871.3661) 
(list 4160.3564 871.3764) 
(list 4160.3716 871.3867) 
(list 4160.3886 871.3969) 
(list 4160.4067 871.4072) 
(list 4160.4254 871.4175) 
(list 4160.4442 871.4278) 
(list 4160.4626 871.4381) 
(list 4160.4799 871.4483) 
(list 4160.4956 871.4586) 
(list 4160.5092 871.4689) 
(list 4160.5204 871.4792) 
(list 4160.5287 871.4894) 
(list 4160.5339 871.4997) 
(list 4160.5359 871.51) 
(list 4160.5359 871.51)))
(apply 'command (append '("pline") coords '("c")))
(setq tap13 (ssadd (entlast) tap13))
(command "_mirror" (entlast) "" "4160,900" "4160,901" "No")
(setq tap13 (ssadd (entlast) tap13))
(setq coords (list 
(list 4161.112 871.14) 
(list 4160.5359 871.14) 
(list 4160.5359 871.1503) 
(list 4160.5359 871.1606) 
(list 4160.5359 871.1708) 
(list 4160.5359 871.1811) 
(list 4160.5359 871.1914) 
(list 4160.5359 871.2017) 
(list 4160.5359 871.2119) 
(list 4160.5359 871.2222) 
(list 4160.5359 871.2325) 
(list 4160.5359 871.2428) 
(list 4160.5359 871.2531) 
(list 4160.5359 871.2633) 
(list 4160.5359 871.2736) 
(list 4160.5359 871.2839) 
(list 4160.5359 871.2942) 
(list 4160.5359 871.3044) 
(list 4160.5359 871.3147) 
(list 4160.5359 871.325) 
(list 4160.5359 871.3353) 
(list 4160.5359 871.3456) 
(list 4160.5359 871.3558) 
(list 4160.5359 871.3661) 
(list 4160.5359 871.3764) 
(list 4160.5359 871.3867) 
(list 4160.5359 871.3969) 
(list 4160.5359 871.4072) 
(list 4160.5359 871.4175) 
(list 4160.5359 871.4278) 
(list 4160.5359 871.4381) 
(list 4160.5359 871.4483) 
(list 4160.5359 871.4586) 
(list 4160.5359 871.4689) 
(list 4160.5359 871.4792) 
(list 4160.5359 871.4894) 
(list 4160.5359 871.4997) 
(list 4160.5359 871.51) 
(list 4161.112 871.51)))
(apply 'command (append '("pline") coords '("c")))
(setq tap13 (ssadd (entlast) tap13))
(command "_mirror" (entlast) "" "4160,900" "4160,901" "No")
(setq tap13 (ssadd (entlast) tap13))
(setq coords (list 
(list 4160 871.51) 
(list 4160.125 871.51) 
(list 4160.125 871.5203) 
(list 4160.125 871.5306) 
(list 4160.125 871.5408) 
(list 4160.125 871.5511) 
(list 4160.125 871.5614) 
(list 4160.125 871.5717) 
(list 4160.125 871.5819) 
(list 4160.125 871.5922) 
(list 4160.125 871.6025) 
(list 4160.125 871.6128) 
(list 4160.125 871.6231) 
(list 4160.125 871.6333) 
(list 4160.125 871.6436) 
(list 4160.125 871.6539) 
(list 4160.125 871.6642) 
(list 4160.125 871.6744) 
(list 4160.125 871.6847) 
(list 4160.125 871.695) 
(list 4160.125 871.7053) 
(list 4160.125 871.7156) 
(list 4160.125 871.7258) 
(list 4160.125 871.7361) 
(list 4160.125 871.7464) 
(list 4160.125 871.7567) 
(list 4160.125 871.7669) 
(list 4160.125 871.7772) 
(list 4160.125 871.7875) 
(list 4160.125 871.7978) 
(list 4160.125 871.8081) 
(list 4160.125 871.8183) 
(list 4160.125 871.8286) 
(list 4160.125 871.8389) 
(list 4160.125 871.8492) 
(list 4160.125 871.8594) 
(list 4160.125 871.8697) 
(list 4160.125 871.88) 
(list 4160 871.88)))
(apply 'command (append '("pline") coords '("c")))
(setq tap13 (ssadd (entlast) tap13))
(command "_mirror" (entlast) "" "4160,900" "4160,901" "No")
(setq tap13 (ssadd (entlast) tap13))
(setq coords (list 
(list 4160.5459 871.51) 
(list 4160.5359 871.51) 
(list 4160.5345 871.5203) 
(list 4160.5298 871.5306) 
(list 4160.5219 871.5408) 
(list 4160.511 871.5511) 
(list 4160.4975 871.5614) 
(list 4160.4818 871.5717) 
(list 4160.4643 871.5819) 
(list 4160.4456 871.5922) 
(list 4160.4262 871.6025) 
(list 4160.4067 871.6128) 
(list 4160.3878 871.6231) 
(list 4160.3699 871.6333) 
(list 4160.3537 871.6436) 
(list 4160.3396 871.6539) 
(list 4160.3281 871.6642) 
(list 4160.3195 871.6744) 
(list 4160.3142 871.6847) 
(list 4160.3123 871.695) 
(list 4160.3138 871.7053) 
(list 4160.3188 871.7156) 
(list 4160.3271 871.7258) 
(list 4160.3385 871.7361) 
(list 4160.3526 871.7464) 
(list 4160.369 871.7567) 
(list 4160.3873 871.7669) 
(list 4160.4068 871.7772) 
(list 4160.427 871.7875) 
(list 4160.4473 871.7978) 
(list 4160.4671 871.8081) 
(list 4160.4857 871.8183) 
(list 4160.5026 871.8286) 
(list 4160.5173 871.8389) 
(list 4160.5293 871.8492) 
(list 4160.5383 871.8594) 
(list 4160.5439 871.8697) 
(list 4160.5459 871.88) 
(list 4160.5459 871.88)))
(apply 'command (append '("pline") coords '("c")))
(setq tap13 (ssadd (entlast) tap13))
(command "_mirror" (entlast) "" "4160,900" "4160,901" "No")
(setq tap13 (ssadd (entlast) tap13))
(setq coords (list 
(list 4161.112 871.51) 
(list 4160.5459 871.51) 
(list 4160.5459 871.5203) 
(list 4160.5459 871.5306) 
(list 4160.5459 871.5408) 
(list 4160.5459 871.5511) 
(list 4160.5459 871.5614) 
(list 4160.5459 871.5717) 
(list 4160.5459 871.5819) 
(list 4160.5459 871.5922) 
(list 4160.5459 871.6025) 
(list 4160.5459 871.6128) 
(list 4160.5459 871.6231) 
(list 4160.5459 871.6333) 
(list 4160.5459 871.6436) 
(list 4160.5459 871.6539) 
(list 4160.5459 871.6642) 
(list 4160.5459 871.6744) 
(list 4160.5459 871.6847) 
(list 4160.5459 871.695) 
(list 4160.5459 871.7053) 
(list 4160.5459 871.7156) 
(list 4160.5459 871.7258) 
(list 4160.5459 871.7361) 
(list 4160.5459 871.7464) 
(list 4160.5459 871.7567) 
(list 4160.5459 871.7669) 
(list 4160.5459 871.7772) 
(list 4160.5459 871.7875) 
(list 4160.5459 871.7978) 
(list 4160.5459 871.8081) 
(list 4160.5459 871.8183) 
(list 4160.5459 871.8286) 
(list 4160.5459 871.8389) 
(list 4160.5459 871.8492) 
(list 4160.5459 871.8594) 
(list 4160.5459 871.8697) 
(list 4160.5459 871.88) 
(list 4161.112 871.88)))
(apply 'command (append '("pline") coords '("c")))
(setq tap13 (ssadd (entlast) tap13))
(command "_mirror" (entlast) "" "4160,900" "4160,901" "No")
(setq tap13 (ssadd (entlast) tap13))
(setq coords (list 
(list 4160 871.88) 
(list 4160.125 871.88) 
(list 4160.125 871.8903) 
(list 4160.125 871.9006) 
(list 4160.125 871.9108) 
(list 4160.125 871.9211) 
(list 4160.125 871.9314) 
(list 4160.125 871.9417) 
(list 4160.125 871.9519) 
(list 4160.125 871.9622) 
(list 4160.125 871.9725) 
(list 4160.125 871.9828) 
(list 4160.125 871.9931) 
(list 4160.125 872.0033) 
(list 4160.125 872.0136) 
(list 4160.125 872.0239) 
(list 4160.125 872.0342) 
(list 4160.125 872.0444) 
(list 4160.125 872.0547) 
(list 4160.125 872.065) 
(list 4160.125 872.0753) 
(list 4160.125 872.0856) 
(list 4160.125 872.0958) 
(list 4160.125 872.1061) 
(list 4160.125 872.1164) 
(list 4160.125 872.1267) 
(list 4160.125 872.1369) 
(list 4160.125 872.1472) 
(list 4160.125 872.1575) 
(list 4160.125 872.1678) 
(list 4160.125 872.1781) 
(list 4160.125 872.1883) 
(list 4160.125 872.1986) 
(list 4160.125 872.2089) 
(list 4160.125 872.2192) 
(list 4160.125 872.2294) 
(list 4160.125 872.2397) 
(list 4160.125 872.25) 
(list 4160 872.25)))
(apply 'command (append '("pline") coords '("c")))
(setq tap13 (ssadd (entlast) tap13))
(command "_mirror" (entlast) "" "4160,900" "4160,901" "No")
(setq tap13 (ssadd (entlast) tap13))
(setq coords (list 
(list 4160.556 871.88) 
(list 4160.5459 871.88) 
(list 4160.5444 871.8903) 
(list 4160.5393 871.9006) 
(list 4160.5308 871.9108) 
(list 4160.5191 871.9211) 
(list 4160.5046 871.9314) 
(list 4160.4876 871.9417) 
(list 4160.4688 871.9519) 
(list 4160.4487 871.9622) 
(list 4160.4278 871.9725) 
(list 4160.4069 871.9828) 
(list 4160.3865 871.9931) 
(list 4160.3673 872.0033) 
(list 4160.3498 872.0136) 
(list 4160.3347 872.0239) 
(list 4160.3224 872.0342) 
(list 4160.3132 872.0444) 
(list 4160.3075 872.0547) 
(list 4160.3054 872.065) 
(list 4160.3071 872.0753) 
(list 4160.3125 872.0856) 
(list 4160.3214 872.0958) 
(list 4160.3336 872.1061) 
(list 4160.3488 872.1164) 
(list 4160.3664 872.1267) 
(list 4160.386 872.1369) 
(list 4160.4069 872.1472) 
(list 4160.4286 872.1575) 
(list 4160.4504 872.1678) 
(list 4160.4716 872.1781) 
(list 4160.4915 872.1883) 
(list 4160.5097 872.1986) 
(list 4160.5254 872.2089) 
(list 4160.5382 872.2192) 
(list 4160.5478 872.2294) 
(list 4160.5538 872.2397) 
(list 4160.556 872.25) 
(list 4160.556 872.25)))
(apply 'command (append '("pline") coords '("c")))
(setq tap13 (ssadd (entlast) tap13))
(command "_mirror" (entlast) "" "4160,900" "4160,901" "No")
(setq tap13 (ssadd (entlast) tap13))
(setq coords (list 
(list 4161.112 871.88) 
(list 4160.556 871.88) 
(list 4160.556 871.8903) 
(list 4160.556 871.9006) 
(list 4160.556 871.9108) 
(list 4160.556 871.9211) 
(list 4160.556 871.9314) 
(list 4160.556 871.9417) 
(list 4160.556 871.9519) 
(list 4160.556 871.9622) 
(list 4160.556 871.9725) 
(list 4160.556 871.9828) 
(list 4160.556 871.9931) 
(list 4160.556 872.0033) 
(list 4160.556 872.0136) 
(list 4160.556 872.0239) 
(list 4160.556 872.0342) 
(list 4160.556 872.0444) 
(list 4160.556 872.0547) 
(list 4160.556 872.065) 
(list 4160.556 872.0753) 
(list 4160.556 872.0856) 
(list 4160.556 872.0958) 
(list 4160.556 872.1061) 
(list 4160.556 872.1164) 
(list 4160.556 872.1267) 
(list 4160.556 872.1369) 
(list 4160.556 872.1472) 
(list 4160.556 872.1575) 
(list 4160.556 872.1678) 
(list 4160.556 872.1781) 
(list 4160.556 872.1883) 
(list 4160.556 872.1986) 
(list 4160.556 872.2089) 
(list 4160.556 872.2192) 
(list 4160.556 872.2294) 
(list 4160.556 872.2397) 
(list 4160.556 872.25) 
(list 4161.112 872.25)))
(apply 'command (append '("pline") coords '("c")))
(setq tap13 (ssadd (entlast) tap13))
(command "_mirror" (entlast) "" "4160,900" "4160,901" "No")
(setq tap13 (ssadd (entlast) tap13))
(command "_block" "blktap13" "4160,900" tap13 "")
(command "_insert" "blktap13" "4160,900" "1" "1" "0")
(command "_insert" "blktap13" "4160,900" "1" "1" "180")
(setq uc13 nil)
(setq uc13 (ssadd))
(setq coords (list 
(list 0 -0.185) 
(list 0.125 -0.185) 
(list 0.125 -0.17472) 
(list 0.125 -0.16444) 
(list 0.125 -0.15417) 
(list 0.125 -0.14389) 
(list 0.125 -0.13361) 
(list 0.125 -0.12333) 
(list 0.125 -0.11306) 
(list 0.125 -0.10278) 
(list 0.125 -0.0925) 
(list 0.125 -0.082222) 
(list 0.125 -0.071944) 
(list 0.125 -0.061667) 
(list 0.125 -0.051389) 
(list 0.125 -0.041111) 
(list 0.125 -0.030833) 
(list 0.125 -0.020556) 
(list 0.125 -0.010278) 
(list 0.125 0) 
(list 0.125 0.010278) 
(list 0.125 0.020556) 
(list 0.125 0.030833) 
(list 0.125 0.041111) 
(list 0.125 0.051389) 
(list 0.125 0.061667) 
(list 0.125 0.071944) 
(list 0.125 0.082222) 
(list 0.125 0.0925) 
(list 0.125 0.10278) 
(list 0.125 0.11306) 
(list 0.125 0.12333) 
(list 0.125 0.13361) 
(list 0.125 0.14389) 
(list 0.125 0.15417) 
(list 0.125 0.16444) 
(list 0.125 0.17472) 
(list 0.125 0.185) 
(list 0 0.185)))
(apply 'command (append '("pline") coords '("c")))
(setq uc13 (ssadd (entlast) uc13))
(setq coords (list 
(list 1.112 -0.185) 
(list 0.556 -0.185) 
(list 0.55407 -0.17472) 
(list 0.54834 -0.16444) 
(list 0.53899 -0.15417) 
(list 0.52629 -0.14389) 
(list 0.51063 -0.13361) 
(list 0.4925 -0.12333) 
(list 0.47244 -0.11306) 
(list 0.45105 -0.10278) 
(list 0.429 -0.0925) 
(list 0.40695 -0.082222) 
(list 0.38556 -0.071944) 
(list 0.3655 -0.061667) 
(list 0.34737 -0.051389) 
(list 0.33171 -0.041111) 
(list 0.31901 -0.030833) 
(list 0.30966 -0.020556) 
(list 0.30393 -0.010278) 
(list 0.302 0) 
(list 0.30393 0.010278) 
(list 0.30966 0.020556) 
(list 0.31901 0.030833) 
(list 0.33171 0.041111) 
(list 0.34737 0.051389) 
(list 0.3655 0.061667) 
(list 0.38556 0.071944) 
(list 0.40695 0.082222) 
(list 0.429 0.0925) 
(list 0.45105 0.10278) 
(list 0.47244 0.11306) 
(list 0.4925 0.12333) 
(list 0.51063 0.13361) 
(list 0.52629 0.14389) 
(list 0.53899 0.15417) 
(list 0.54834 0.16444) 
(list 0.55407 0.17472) 
(list 0.556 0.185) 
(list 1.112 0.185)))
(apply 'command (append '("pline") coords '("c")))
(setq uc13 (ssadd (entlast) uc13))
(command "_block" "blkuc13" "0,0.185" uc13 "")
(command "_insert" "blkuc13" "4160,872.62" "1" "1" "0")
(command "_insert" "blkuc13" "4160,872.25" "1" "1" "180")
(command "_insert" "blkuc13" "4160,872.99" "1" "1" "0")
(command "_insert" "blkuc13" "4160,872.62" "1" "1" "180")
(command "_insert" "blkuc13" "4160,873.36" "1" "1" "0")
(command "_insert" "blkuc13" "4160,872.99" "1" "1" "180")
(command "_insert" "blkuc13" "4160,873.73" "1" "1" "0")
(command "_insert" "blkuc13" "4160,873.36" "1" "1" "180")
(command "_insert" "blkuc13" "4160,874.1" "1" "1" "0")
(command "_insert" "blkuc13" "4160,873.73" "1" "1" "180")
(command "_insert" "blkuc13" "4160,874.47" "1" "1" "0")
(command "_insert" "blkuc13" "4160,874.1" "1" "1" "180")
(command "_insert" "blkuc13" "4160,874.84" "1" "1" "0")
(command "_insert" "blkuc13" "4160,874.47" "1" "1" "180")
(command "_insert" "blkuc13" "4160,875.21" "1" "1" "0")
(command "_insert" "blkuc13" "4160,874.84" "1" "1" "180")
(command "_insert" "blkuc13" "4160,875.58" "1" "1" "0")
(command "_insert" "blkuc13" "4160,875.21" "1" "1" "180")
(command "_insert" "blkuc13" "4160,875.95" "1" "1" "0")
(command "_insert" "blkuc13" "4160,875.58" "1" "1" "180")
(command "_insert" "blkuc13" "4160,876.32" "1" "1" "0")
(command "_insert" "blkuc13" "4160,875.95" "1" "1" "180")
(command "_insert" "blkuc13" "4160,876.69" "1" "1" "0")
(command "_insert" "blkuc13" "4160,876.32" "1" "1" "180")
(command "_insert" "blkuc13" "4160,877.06" "1" "1" "0")
(command "_insert" "blkuc13" "4160,876.69" "1" "1" "180")
(command "_insert" "blkuc13" "4160,877.43" "1" "1" "0")
(command "_insert" "blkuc13" "4160,877.06" "1" "1" "180")
(command "_insert" "blkuc13" "4160,877.8" "1" "1" "0")
(command "_insert" "blkuc13" "4160,877.43" "1" "1" "180")
(command "_insert" "blkuc13" "4160,878.17" "1" "1" "0")
(command "_insert" "blkuc13" "4160,877.8" "1" "1" "180")
(command "_insert" "blkuc13" "4160,878.54" "1" "1" "0")
(command "_insert" "blkuc13" "4160,878.17" "1" "1" "180")
(command "_insert" "blkuc13" "4160,878.91" "1" "1" "0")
(command "_insert" "blkuc13" "4160,878.54" "1" "1" "180")
(command "_insert" "blkuc13" "4160,879.28" "1" "1" "0")
(command "_insert" "blkuc13" "4160,878.91" "1" "1" "180")
(command "_insert" "blkuc13" "4160,879.65" "1" "1" "0")
(command "_insert" "blkuc13" "4160,879.28" "1" "1" "180")
(command "_insert" "blkuc13" "4160,880.02" "1" "1" "0")
(command "_insert" "blkuc13" "4160,879.65" "1" "1" "180")
(command "_insert" "blkuc13" "4160,880.39" "1" "1" "0")
(command "_insert" "blkuc13" "4160,880.02" "1" "1" "180")
(command "_insert" "blkuc13" "4160,880.76" "1" "1" "0")
(command "_insert" "blkuc13" "4160,880.39" "1" "1" "180")
(command "_insert" "blkuc13" "4160,881.13" "1" "1" "0")
(command "_insert" "blkuc13" "4160,880.76" "1" "1" "180")
(command "_insert" "blkuc13" "4160,881.5" "1" "1" "0")
(command "_insert" "blkuc13" "4160,881.13" "1" "1" "180")
(command "_insert" "blkuc13" "4160,881.87" "1" "1" "0")
(command "_insert" "blkuc13" "4160,881.5" "1" "1" "180")
(command "_insert" "blkuc13" "4160,882.24" "1" "1" "0")
(command "_insert" "blkuc13" "4160,881.87" "1" "1" "180")
(command "_insert" "blkuc13" "4160,882.61" "1" "1" "0")
(command "_insert" "blkuc13" "4160,882.24" "1" "1" "180")
(command "_insert" "blkuc13" "4160,882.98" "1" "1" "0")
(command "_insert" "blkuc13" "4160,882.61" "1" "1" "180")
(command "_insert" "blkuc13" "4160,883.35" "1" "1" "0")
(command "_insert" "blkuc13" "4160,882.98" "1" "1" "180")
(command "_insert" "blkuc13" "4160,883.72" "1" "1" "0")
(command "_insert" "blkuc13" "4160,883.35" "1" "1" "180")
(command "_insert" "blkuc13" "4160,884.09" "1" "1" "0")
(command "_insert" "blkuc13" "4160,883.72" "1" "1" "180")
(command "_insert" "blkuc13" "4160,884.46" "1" "1" "0")
(command "_insert" "blkuc13" "4160,884.09" "1" "1" "180")
(command "_insert" "blkuc13" "4160,884.83" "1" "1" "0")
(command "_insert" "blkuc13" "4160,884.46" "1" "1" "180")
(command "_insert" "blkuc13" "4160,885.2" "1" "1" "0")
(command "_insert" "blkuc13" "4160,884.83" "1" "1" "180")
(command "_insert" "blkuc13" "4160,885.57" "1" "1" "0")
(command "_insert" "blkuc13" "4160,885.2" "1" "1" "180")
(command "_insert" "blkuc13" "4160,885.94" "1" "1" "0")
(command "_insert" "blkuc13" "4160,885.57" "1" "1" "180")
(command "_insert" "blkuc13" "4160,886.31" "1" "1" "0")
(command "_insert" "blkuc13" "4160,885.94" "1" "1" "180")
(command "_insert" "blkuc13" "4160,886.68" "1" "1" "0")
(command "_insert" "blkuc13" "4160,886.31" "1" "1" "180")
(command "_insert" "blkuc13" "4160,887.05" "1" "1" "0")
(command "_insert" "blkuc13" "4160,886.68" "1" "1" "180")
(command "_insert" "blkuc13" "4160,887.42" "1" "1" "0")
(command "_insert" "blkuc13" "4160,887.05" "1" "1" "180")
(command "_insert" "blkuc13" "4160,887.79" "1" "1" "0")
(command "_insert" "blkuc13" "4160,887.42" "1" "1" "180")
(command "_insert" "blkuc13" "4160,888.16" "1" "1" "0")
(command "_insert" "blkuc13" "4160,887.79" "1" "1" "180")
(command "_insert" "blkuc13" "4160,888.53" "1" "1" "0")
(command "_insert" "blkuc13" "4160,888.16" "1" "1" "180")
(command "_insert" "blkuc13" "4160,888.9" "1" "1" "0")
(command "_insert" "blkuc13" "4160,888.53" "1" "1" "180")
(command "_insert" "blkuc13" "4160,889.27" "1" "1" "0")
(command "_insert" "blkuc13" "4160,888.9" "1" "1" "180")
(command "_insert" "blkuc13" "4160,889.64" "1" "1" "0")
(command "_insert" "blkuc13" "4160,889.27" "1" "1" "180")
(command "_insert" "blkuc13" "4160,890.01" "1" "1" "0")
(command "_insert" "blkuc13" "4160,889.64" "1" "1" "180")
(command "_insert" "blkuc13" "4160,890.38" "1" "1" "0")
(command "_insert" "blkuc13" "4160,890.01" "1" "1" "180")
(command "_insert" "blkuc13" "4160,890.75" "1" "1" "0")
(command "_insert" "blkuc13" "4160,890.38" "1" "1" "180")
(command "_insert" "blkuc13" "4160,891.12" "1" "1" "0")
(command "_insert" "blkuc13" "4160,890.75" "1" "1" "180")
(command "_insert" "blkuc13" "4160,891.49" "1" "1" "0")
(command "_insert" "blkuc13" "4160,891.12" "1" "1" "180")
(command "_insert" "blkuc13" "4160,891.86" "1" "1" "0")
(command "_insert" "blkuc13" "4160,891.49" "1" "1" "180")
(command "_insert" "blkuc13" "4160,892.23" "1" "1" "0")
(command "_insert" "blkuc13" "4160,891.86" "1" "1" "180")
(command "_insert" "blkuc13" "4160,892.6" "1" "1" "0")
(command "_insert" "blkuc13" "4160,892.23" "1" "1" "180")
(command "_insert" "blkuc13" "4160,892.97" "1" "1" "0")
(command "_insert" "blkuc13" "4160,892.6" "1" "1" "180")
(command "_insert" "blkuc13" "4160,893.34" "1" "1" "0")
(command "_insert" "blkuc13" "4160,892.97" "1" "1" "180")
(command "_insert" "blkuc13" "4160,893.71" "1" "1" "0")
(command "_insert" "blkuc13" "4160,893.34" "1" "1" "180")
(command "_insert" "blkuc13" "4160,894.08" "1" "1" "0")
(command "_insert" "blkuc13" "4160,893.71" "1" "1" "180")
(command "_insert" "blkuc13" "4160,894.45" "1" "1" "0")
(command "_insert" "blkuc13" "4160,894.08" "1" "1" "180")
(command "_insert" "blkuc13" "4160,894.82" "1" "1" "0")
(command "_insert" "blkuc13" "4160,894.45" "1" "1" "180")
(command "_insert" "blkuc13" "4160,895.19" "1" "1" "0")
(command "_insert" "blkuc13" "4160,894.82" "1" "1" "180")
(command "_insert" "blkuc13" "4160,895.56" "1" "1" "0")
(command "_insert" "blkuc13" "4160,895.19" "1" "1" "180")
(command "_insert" "blkuc13" "4160,895.93" "1" "1" "0")
(command "_insert" "blkuc13" "4160,895.56" "1" "1" "180")
(command "_insert" "blkuc13" "4160,896.3" "1" "1" "0")
(command "_insert" "blkuc13" "4160,895.93" "1" "1" "180")
(command "_insert" "blkuc13" "4160,896.67" "1" "1" "0")
(command "_insert" "blkuc13" "4160,896.3" "1" "1" "180")
(command "_insert" "blkuc13" "4160,897.04" "1" "1" "0")
(command "_insert" "blkuc13" "4160,896.67" "1" "1" "180")
(command "_insert" "blkuc13" "4160,897.41" "1" "1" "0")
(command "_insert" "blkuc13" "4160,897.04" "1" "1" "180")
(command "_insert" "blkuc13" "4160,897.78" "1" "1" "0")
(command "_insert" "blkuc13" "4160,897.41" "1" "1" "180")
(command "_insert" "blkuc13" "4160,898.15" "1" "1" "0")
(command "_insert" "blkuc13" "4160,897.78" "1" "1" "180")
(command "_insert" "blkuc13" "4160,898.52" "1" "1" "0")
(command "_insert" "blkuc13" "4160,898.15" "1" "1" "180")
(command "_insert" "blkuc13" "4160,898.89" "1" "1" "0")
(command "_insert" "blkuc13" "4160,898.52" "1" "1" "180")
(command "_insert" "blkuc13" "4160,899.26" "1" "1" "0")
(command "_insert" "blkuc13" "4160,898.89" "1" "1" "180")
(command "_insert" "blkuc13" "4160,899.63" "1" "1" "0")
(command "_insert" "blkuc13" "4160,899.26" "1" "1" "180")
(command "_insert" "blkuc13" "4160,900" "1" "1" "0")
(command "_insert" "blkuc13" "4160,899.63" "1" "1" "180")
(command "_insert" "blkuc13" "4160,900.37" "1" "1" "0")
(command "_insert" "blkuc13" "4160,900" "1" "1" "180")
(command "_insert" "blkuc13" "4160,900.74" "1" "1" "0")
(command "_insert" "blkuc13" "4160,900.37" "1" "1" "180")
(command "_insert" "blkuc13" "4160,901.11" "1" "1" "0")
(command "_insert" "blkuc13" "4160,900.74" "1" "1" "180")
(command "_insert" "blkuc13" "4160,901.48" "1" "1" "0")
(command "_insert" "blkuc13" "4160,901.11" "1" "1" "180")
(command "_insert" "blkuc13" "4160,901.85" "1" "1" "0")
(command "_insert" "blkuc13" "4160,901.48" "1" "1" "180")
(command "_insert" "blkuc13" "4160,902.22" "1" "1" "0")
(command "_insert" "blkuc13" "4160,901.85" "1" "1" "180")
(command "_insert" "blkuc13" "4160,902.59" "1" "1" "0")
(command "_insert" "blkuc13" "4160,902.22" "1" "1" "180")
(command "_insert" "blkuc13" "4160,902.96" "1" "1" "0")
(command "_insert" "blkuc13" "4160,902.59" "1" "1" "180")
(command "_insert" "blkuc13" "4160,903.33" "1" "1" "0")
(command "_insert" "blkuc13" "4160,902.96" "1" "1" "180")
(command "_insert" "blkuc13" "4160,903.7" "1" "1" "0")
(command "_insert" "blkuc13" "4160,903.33" "1" "1" "180")
(command "_insert" "blkuc13" "4160,904.07" "1" "1" "0")
(command "_insert" "blkuc13" "4160,903.7" "1" "1" "180")
(command "_insert" "blkuc13" "4160,904.44" "1" "1" "0")
(command "_insert" "blkuc13" "4160,904.07" "1" "1" "180")
(command "_insert" "blkuc13" "4160,904.81" "1" "1" "0")
(command "_insert" "blkuc13" "4160,904.44" "1" "1" "180")
(command "_insert" "blkuc13" "4160,905.18" "1" "1" "0")
(command "_insert" "blkuc13" "4160,904.81" "1" "1" "180")
(command "_insert" "blkuc13" "4160,905.55" "1" "1" "0")
(command "_insert" "blkuc13" "4160,905.18" "1" "1" "180")
(command "_insert" "blkuc13" "4160,905.92" "1" "1" "0")
(command "_insert" "blkuc13" "4160,905.55" "1" "1" "180")
(command "_insert" "blkuc13" "4160,906.29" "1" "1" "0")
(command "_insert" "blkuc13" "4160,905.92" "1" "1" "180")
(command "_insert" "blkuc13" "4160,906.66" "1" "1" "0")
(command "_insert" "blkuc13" "4160,906.29" "1" "1" "180")
(command "_insert" "blkuc13" "4160,907.03" "1" "1" "0")
(command "_insert" "blkuc13" "4160,906.66" "1" "1" "180")
(command "_insert" "blkuc13" "4160,907.4" "1" "1" "0")
(command "_insert" "blkuc13" "4160,907.03" "1" "1" "180")
(command "_insert" "blkuc13" "4160,907.77" "1" "1" "0")
(command "_insert" "blkuc13" "4160,907.4" "1" "1" "180")
(command "_insert" "blkuc13" "4160,908.14" "1" "1" "0")
(command "_insert" "blkuc13" "4160,907.77" "1" "1" "180")
(command "_insert" "blkuc13" "4160,908.51" "1" "1" "0")
(command "_insert" "blkuc13" "4160,908.14" "1" "1" "180")
(command "_insert" "blkuc13" "4160,908.88" "1" "1" "0")
(command "_insert" "blkuc13" "4160,908.51" "1" "1" "180")
(command "_insert" "blkuc13" "4160,909.25" "1" "1" "0")
(command "_insert" "blkuc13" "4160,908.88" "1" "1" "180")
(command "_insert" "blkuc13" "4160,909.62" "1" "1" "0")
(command "_insert" "blkuc13" "4160,909.25" "1" "1" "180")
(command "_insert" "blkuc13" "4160,909.99" "1" "1" "0")
(command "_insert" "blkuc13" "4160,909.62" "1" "1" "180")
(command "_insert" "blkuc13" "4160,910.36" "1" "1" "0")
(command "_insert" "blkuc13" "4160,909.99" "1" "1" "180")
(command "_insert" "blkuc13" "4160,910.73" "1" "1" "0")
(command "_insert" "blkuc13" "4160,910.36" "1" "1" "180")
(command "_insert" "blkuc13" "4160,911.1" "1" "1" "0")
(command "_insert" "blkuc13" "4160,910.73" "1" "1" "180")
(command "_insert" "blkuc13" "4160,911.47" "1" "1" "0")
(command "_insert" "blkuc13" "4160,911.1" "1" "1" "180")
(command "_insert" "blkuc13" "4160,911.84" "1" "1" "0")
(command "_insert" "blkuc13" "4160,911.47" "1" "1" "180")
(command "_insert" "blkuc13" "4160,912.21" "1" "1" "0")
(command "_insert" "blkuc13" "4160,911.84" "1" "1" "180")
(command "_insert" "blkuc13" "4160,912.58" "1" "1" "0")
(command "_insert" "blkuc13" "4160,912.21" "1" "1" "180")
(command "_insert" "blkuc13" "4160,912.95" "1" "1" "0")
(command "_insert" "blkuc13" "4160,912.58" "1" "1" "180")
(command "_insert" "blkuc13" "4160,913.32" "1" "1" "0")
(command "_insert" "blkuc13" "4160,912.95" "1" "1" "180")
(command "_insert" "blkuc13" "4160,913.69" "1" "1" "0")
(command "_insert" "blkuc13" "4160,913.32" "1" "1" "180")
(command "_insert" "blkuc13" "4160,914.06" "1" "1" "0")
(command "_insert" "blkuc13" "4160,913.69" "1" "1" "180")
(command "_insert" "blkuc13" "4160,914.43" "1" "1" "0")
(command "_insert" "blkuc13" "4160,914.06" "1" "1" "180")
(command "_insert" "blkuc13" "4160,914.8" "1" "1" "0")
(command "_insert" "blkuc13" "4160,914.43" "1" "1" "180")
(command "_insert" "blkuc13" "4160,915.17" "1" "1" "0")
(command "_insert" "blkuc13" "4160,914.8" "1" "1" "180")
(command "_insert" "blkuc13" "4160,915.54" "1" "1" "0")
(command "_insert" "blkuc13" "4160,915.17" "1" "1" "180")
(command "_insert" "blkuc13" "4160,915.91" "1" "1" "0")
(command "_insert" "blkuc13" "4160,915.54" "1" "1" "180")
(command "_insert" "blkuc13" "4160,916.28" "1" "1" "0")
(command "_insert" "blkuc13" "4160,915.91" "1" "1" "180")
(command "_insert" "blkuc13" "4160,916.65" "1" "1" "0")
(command "_insert" "blkuc13" "4160,916.28" "1" "1" "180")
(command "_insert" "blkuc13" "4160,917.02" "1" "1" "0")
(command "_insert" "blkuc13" "4160,916.65" "1" "1" "180")
(command "_insert" "blkuc13" "4160,917.39" "1" "1" "0")
(command "_insert" "blkuc13" "4160,917.02" "1" "1" "180")
(command "_insert" "blkuc13" "4160,917.76" "1" "1" "0")
(command "_insert" "blkuc13" "4160,917.39" "1" "1" "180")
(command "_insert" "blkuc13" "4160,918.13" "1" "1" "0")
(command "_insert" "blkuc13" "4160,917.76" "1" "1" "180")
(command "_insert" "blkuc13" "4160,918.5" "1" "1" "0")
(command "_insert" "blkuc13" "4160,918.13" "1" "1" "180")
(command "_insert" "blkuc13" "4160,918.87" "1" "1" "0")
(command "_insert" "blkuc13" "4160,918.5" "1" "1" "180")
(command "_insert" "blkuc13" "4160,919.24" "1" "1" "0")
(command "_insert" "blkuc13" "4160,918.87" "1" "1" "180")
(command "_insert" "blkuc13" "4160,919.61" "1" "1" "0")
(command "_insert" "blkuc13" "4160,919.24" "1" "1" "180")
(command "_insert" "blkuc13" "4160,919.98" "1" "1" "0")
(command "_insert" "blkuc13" "4160,919.61" "1" "1" "180")
(command "_insert" "blkuc13" "4160,920.35" "1" "1" "0")
(command "_insert" "blkuc13" "4160,919.98" "1" "1" "180")
(command "_insert" "blkuc13" "4160,920.72" "1" "1" "0")
(command "_insert" "blkuc13" "4160,920.35" "1" "1" "180")
(command "_insert" "blkuc13" "4160,921.09" "1" "1" "0")
(command "_insert" "blkuc13" "4160,920.72" "1" "1" "180")
(command "_insert" "blkuc13" "4160,921.46" "1" "1" "0")
(command "_insert" "blkuc13" "4160,921.09" "1" "1" "180")
(command "_insert" "blkuc13" "4160,921.83" "1" "1" "0")
(command "_insert" "blkuc13" "4160,921.46" "1" "1" "180")
(command "_insert" "blkuc13" "4160,922.2" "1" "1" "0")
(command "_insert" "blkuc13" "4160,921.83" "1" "1" "180")
(command "_insert" "blkuc13" "4160,922.57" "1" "1" "0")
(command "_insert" "blkuc13" "4160,922.2" "1" "1" "180")
(command "_insert" "blkuc13" "4160,922.94" "1" "1" "0")
(command "_insert" "blkuc13" "4160,922.57" "1" "1" "180")
(command "_insert" "blkuc13" "4160,923.31" "1" "1" "0")
(command "_insert" "blkuc13" "4160,922.94" "1" "1" "180")
(command "_insert" "blkuc13" "4160,923.68" "1" "1" "0")
(command "_insert" "blkuc13" "4160,923.31" "1" "1" "180")
(command "_insert" "blkuc13" "4160,924.05" "1" "1" "0")
(command "_insert" "blkuc13" "4160,923.68" "1" "1" "180")
(command "_insert" "blkuc13" "4160,924.42" "1" "1" "0")
(command "_insert" "blkuc13" "4160,924.05" "1" "1" "180")
(command "_insert" "blkuc13" "4160,924.79" "1" "1" "0")
(command "_insert" "blkuc13" "4160,924.42" "1" "1" "180")
(command "_insert" "blkuc13" "4160,925.16" "1" "1" "0")
(command "_insert" "blkuc13" "4160,924.79" "1" "1" "180")
(command "_insert" "blkuc13" "4160,925.53" "1" "1" "0")
(command "_insert" "blkuc13" "4160,925.16" "1" "1" "180")
(command "_insert" "blkuc13" "4160,925.9" "1" "1" "0")
(command "_insert" "blkuc13" "4160,925.53" "1" "1" "180")
(command "_insert" "blkuc13" "4160,926.27" "1" "1" "0")
(command "_insert" "blkuc13" "4160,925.9" "1" "1" "180")
(command "_insert" "blkuc13" "4160,926.64" "1" "1" "0")
(command "_insert" "blkuc13" "4160,926.27" "1" "1" "180")
(command "_insert" "blkuc13" "4160,927.01" "1" "1" "0")
(command "_insert" "blkuc13" "4160,926.64" "1" "1" "180")
(command "_insert" "blkuc13" "4160,927.38" "1" "1" "0")
(command "_insert" "blkuc13" "4160,927.01" "1" "1" "180")
(command "_insert" "blkuc13" "4160,927.75" "1" "1" "0")
(command "_insert" "blkuc13" "4160,927.38" "1" "1" "180")
(command "_layer" "set" "phccover" "")
(command "_rectangle" "4158.888,933.3" "4161.112,866.7")
(command "_layer" "set" "nitride" "")
(setq phc13 currobj)
(command "_layer" "set" "cover" "")
(command "_rectangle" "4158.888,836.7" "4161.112,963.3")
(command "_layer" "set" "nitride" "")
(command "_layer" "set" "text" "")
(command "_circle" "4157.938,846.7" "0.075")
(command "_circle" "4157.563,846.7" "0.15")
(command "_circle" "4157.188,846.7" "0.075")
(command "_circle" "4156.813,846.7" "0.15")
(command "_circle" "4157.938,848.7" "0.075")
(command "_circle" "4157.563,848.7" "0.075")
(command "_circle" "4157.188,848.7" "0.15")
(command "_circle" "4156.813,848.7" "0.15")
(command "_circle" "4157.938,850.7" "0.075")
(command "_circle" "4157.563,850.7" "0.15")
(command "_circle" "4157.188,850.7" "0.15")
(command "_circle" "4156.813,850.7" "0.15")
(command "_circle" "4157.938,852.7" "0.075")
(command "_circle" "4157.563,852.7" "0.075")
(command "_circle" "4157.188,852.7" "0.075")
(command "_circle" "4156.813,852.7" "0.075")
(command "_circle" "4156.438,852.7" "0.15")
(command "_circle" "4157.938,854.7" "0.075")
(command "_circle" "4157.563,854.7" "0.15")
(command "_circle" "4157.188,854.7" "0.075")
(command "_circle" "4156.813,854.7" "0.075")
(command "_circle" "4156.438,854.7" "0.15")
(command "_circle" "4157.938,856.7" "0.075")
(command "_circle" "4157.563,856.7" "0.075")
(command "_circle" "4157.188,856.7" "0.15")
(command "_circle" "4156.813,856.7" "0.075")
(command "_circle" "4156.438,856.7" "0.15")
(command "_circle" "4157.938,858.7" "0.075")
(command "_circle" "4157.563,858.7" "0.15")
(command "_circle" "4157.188,858.7" "0.15")
(command "_circle" "4156.813,858.7" "0.075")
(command "_circle" "4156.438,858.7" "0.15")
(command "_circle" "4157.938,860.7" "0.075")
(command "_circle" "4157.563,860.7" "0.075")
(command "_circle" "4157.188,860.7" "0.075")
(command "_circle" "4156.813,860.7" "0.15")
(command "_circle" "4156.438,860.7" "0.15")
(command "_circle" "4157.938,862.7" "0.075")
(command "_circle" "4157.563,862.7" "0.15")
(command "_circle" "4157.188,862.7" "0.075")
(command "_circle" "4156.813,862.7" "0.15")
(command "_circle" "4156.438,862.7" "0.15")
(command "_circle" "4157.938,864.7" "0.075")
(command "_circle" "4157.563,864.7" "0.075")
(command "_circle" "4157.188,864.7" "0.15")
(command "_circle" "4156.813,864.7" "0.15")
(command "_circle" "4156.438,864.7" "0.15")
(command "_circle" "4157.938,866.7" "0.075")
(command "_circle" "4157.563,866.7" "0.15")
(command "_circle" "4157.188,866.7" "0.15")
(command "_circle" "4156.813,866.7" "0.15")
(command "_circle" "4156.438,866.7" "0.15")
(command "_circle" "4157.938,868.7" "0.075")
(command "_circle" "4157.563,868.7" "0.075")
(command "_circle" "4157.188,868.7" "0.075")
(command "_circle" "4156.813,868.7" "0.075")
(command "_circle" "4156.438,868.7" "0.075")
(command "_circle" "4156.063,868.7" "0.15")
(command "_circle" "4157.938,870.7" "0.075")
(command "_circle" "4157.563,870.7" "0.15")
(command "_circle" "4157.188,870.7" "0.075")
(command "_circle" "4156.813,870.7" "0.075")
(command "_circle" "4156.438,870.7" "0.075")
(command "_circle" "4156.063,870.7" "0.15")
(command "_circle" "4157.938,872.7" "0.075")
(command "_circle" "4157.563,872.7" "0.075")
(command "_circle" "4157.188,872.7" "0.15")
(command "_circle" "4156.813,872.7" "0.075")
(command "_circle" "4156.438,872.7" "0.075")
(command "_circle" "4156.063,872.7" "0.15")
(command "_circle" "4157.938,874.7" "0.075")
(command "_circle" "4157.563,874.7" "0.15")
(command "_circle" "4157.188,874.7" "0.15")
(command "_circle" "4156.813,874.7" "0.075")
(command "_circle" "4156.438,874.7" "0.075")
(command "_circle" "4156.063,874.7" "0.15")
(command "_circle" "4157.938,876.7" "0.075")
(command "_circle" "4157.563,876.7" "0.075")
(command "_circle" "4157.188,876.7" "0.075")
(command "_circle" "4156.813,876.7" "0.15")
(command "_circle" "4156.438,876.7" "0.075")
(command "_circle" "4156.063,876.7" "0.15")
(command "_circle" "4157.938,878.7" "0.075")
(command "_circle" "4157.563,878.7" "0.15")
(command "_circle" "4157.188,878.7" "0.075")
(command "_circle" "4156.813,878.7" "0.15")
(command "_circle" "4156.438,878.7" "0.075")
(command "_circle" "4156.063,878.7" "0.15")
(command "_circle" "4157.938,880.7" "0.075")
(command "_circle" "4157.563,880.7" "0.075")
(command "_circle" "4157.188,880.7" "0.15")
(command "_circle" "4156.813,880.7" "0.15")
(command "_circle" "4156.438,880.7" "0.075")
(command "_circle" "4156.063,880.7" "0.15")
(command "_circle" "4157.938,882.7" "0.075")
(command "_circle" "4157.563,882.7" "0.15")
(command "_circle" "4157.188,882.7" "0.15")
(command "_circle" "4156.813,882.7" "0.15")
(command "_circle" "4156.438,882.7" "0.075")
(command "_circle" "4156.063,882.7" "0.15")
(command "_circle" "4157.938,884.7" "0.075")
(command "_circle" "4157.563,884.7" "0.075")
(command "_circle" "4157.188,884.7" "0.075")
(command "_circle" "4156.813,884.7" "0.075")
(command "_circle" "4156.438,884.7" "0.15")
(command "_circle" "4156.063,884.7" "0.15")
(command "_circle" "4157.938,886.7" "0.075")
(command "_circle" "4157.563,886.7" "0.15")
(command "_circle" "4157.188,886.7" "0.075")
(command "_circle" "4156.813,886.7" "0.075")
(command "_circle" "4156.438,886.7" "0.15")
(command "_circle" "4156.063,886.7" "0.15")
(command "_circle" "4157.938,888.7" "0.075")
(command "_circle" "4157.563,888.7" "0.075")
(command "_circle" "4157.188,888.7" "0.15")
(command "_circle" "4156.813,888.7" "0.075")
(command "_circle" "4156.438,888.7" "0.15")
(command "_circle" "4156.063,888.7" "0.15")
(command "_circle" "4157.938,890.7" "0.075")
(command "_circle" "4157.563,890.7" "0.15")
(command "_circle" "4157.188,890.7" "0.15")
(command "_circle" "4156.813,890.7" "0.075")
(command "_circle" "4156.438,890.7" "0.15")
(command "_circle" "4156.063,890.7" "0.15")
(command "_circle" "4157.938,892.7" "0.075")
(command "_circle" "4157.563,892.7" "0.075")
(command "_circle" "4157.188,892.7" "0.075")
(command "_circle" "4156.813,892.7" "0.15")
(command "_circle" "4156.438,892.7" "0.15")
(command "_circle" "4156.063,892.7" "0.15")
(command "_circle" "4157.938,894.7" "0.075")
(command "_circle" "4157.563,894.7" "0.15")
(command "_circle" "4157.188,894.7" "0.075")
(command "_circle" "4156.813,894.7" "0.15")
(command "_circle" "4156.438,894.7" "0.15")
(command "_circle" "4156.063,894.7" "0.15")
(command "_circle" "4157.938,896.7" "0.075")
(command "_circle" "4157.563,896.7" "0.075")
(command "_circle" "4157.188,896.7" "0.15")
(command "_circle" "4156.813,896.7" "0.15")
(command "_circle" "4156.438,896.7" "0.15")
(command "_circle" "4156.063,896.7" "0.15")
(command "_circle" "4157.938,898.7" "0.075")
(command "_circle" "4157.563,898.7" "0.15")
(command "_circle" "4157.188,898.7" "0.15")
(command "_circle" "4156.813,898.7" "0.15")
(command "_circle" "4156.438,898.7" "0.15")
(command "_circle" "4156.063,898.7" "0.15")
(command "_circle" "4157.938,900.7" "0.075")
(command "_circle" "4157.563,900.7" "0.075")
(command "_circle" "4157.188,900.7" "0.075")
(command "_circle" "4156.813,900.7" "0.075")
(command "_circle" "4156.438,900.7" "0.075")
(command "_circle" "4156.063,900.7" "0.075")
(command "_circle" "4155.688,900.7" "0.15")
(command "_circle" "4157.938,902.7" "0.075")
(command "_circle" "4157.563,902.7" "0.15")
(command "_circle" "4157.188,902.7" "0.075")
(command "_circle" "4156.813,902.7" "0.075")
(command "_circle" "4156.438,902.7" "0.075")
(command "_circle" "4156.063,902.7" "0.075")
(command "_circle" "4155.688,902.7" "0.15")
(command "_circle" "4157.938,904.7" "0.075")
(command "_circle" "4157.563,904.7" "0.075")
(command "_circle" "4157.188,904.7" "0.15")
(command "_circle" "4156.813,904.7" "0.075")
(command "_circle" "4156.438,904.7" "0.075")
(command "_circle" "4156.063,904.7" "0.075")
(command "_circle" "4155.688,904.7" "0.15")
(command "_circle" "4157.938,906.7" "0.075")
(command "_circle" "4157.563,906.7" "0.15")
(command "_circle" "4157.188,906.7" "0.15")
(command "_circle" "4156.813,906.7" "0.075")
(command "_circle" "4156.438,906.7" "0.075")
(command "_circle" "4156.063,906.7" "0.075")
(command "_circle" "4155.688,906.7" "0.15")
(command "_circle" "4157.938,908.7" "0.075")
(command "_circle" "4157.563,908.7" "0.075")
(command "_circle" "4157.188,908.7" "0.075")
(command "_circle" "4156.813,908.7" "0.15")
(command "_circle" "4156.438,908.7" "0.075")
(command "_circle" "4156.063,908.7" "0.075")
(command "_circle" "4155.688,908.7" "0.15")
(command "_circle" "4157.938,910.7" "0.075")
(command "_circle" "4157.563,910.7" "0.15")
(command "_circle" "4157.188,910.7" "0.075")
(command "_circle" "4156.813,910.7" "0.15")
(command "_circle" "4156.438,910.7" "0.075")
(command "_circle" "4156.063,910.7" "0.075")
(command "_circle" "4155.688,910.7" "0.15")
(command "_circle" "4157.938,912.7" "0.075")
(command "_circle" "4157.563,912.7" "0.075")
(command "_circle" "4157.188,912.7" "0.15")
(command "_circle" "4156.813,912.7" "0.15")
(command "_circle" "4156.438,912.7" "0.075")
(command "_circle" "4156.063,912.7" "0.075")
(command "_circle" "4155.688,912.7" "0.15")
(command "_circle" "4157.938,914.7" "0.075")
(command "_circle" "4157.563,914.7" "0.15")
(command "_circle" "4157.188,914.7" "0.15")
(command "_circle" "4156.813,914.7" "0.15")
(command "_circle" "4156.438,914.7" "0.075")
(command "_circle" "4156.063,914.7" "0.075")
(command "_circle" "4155.688,914.7" "0.15")
(command "_circle" "4157.938,916.7" "0.075")
(command "_circle" "4157.563,916.7" "0.075")
(command "_circle" "4157.188,916.7" "0.075")
(command "_circle" "4156.813,916.7" "0.075")
(command "_circle" "4156.438,916.7" "0.15")
(command "_circle" "4156.063,916.7" "0.075")
(command "_circle" "4155.688,916.7" "0.15")
(command "_circle" "4157.938,918.7" "0.075")
(command "_circle" "4157.563,918.7" "0.15")
(command "_circle" "4157.188,918.7" "0.075")
(command "_circle" "4156.813,918.7" "0.075")
(command "_circle" "4156.438,918.7" "0.15")
(command "_circle" "4156.063,918.7" "0.075")
(command "_circle" "4155.688,918.7" "0.15")
(command "_circle" "4157.938,920.7" "0.075")
(command "_circle" "4157.563,920.7" "0.075")
(command "_circle" "4157.188,920.7" "0.15")
(command "_circle" "4156.813,920.7" "0.075")
(command "_circle" "4156.438,920.7" "0.15")
(command "_circle" "4156.063,920.7" "0.075")
(command "_circle" "4155.688,920.7" "0.15")
(command "_circle" "4157.938,922.7" "0.075")
(command "_circle" "4157.563,922.7" "0.15")
(command "_circle" "4157.188,922.7" "0.15")
(command "_circle" "4156.813,922.7" "0.075")
(command "_circle" "4156.438,922.7" "0.15")
(command "_circle" "4156.063,922.7" "0.075")
(command "_circle" "4155.688,922.7" "0.15")
(command "_circle" "4157.938,924.7" "0.075")
(command "_circle" "4157.563,924.7" "0.075")
(command "_circle" "4157.188,924.7" "0.075")
(command "_circle" "4156.813,924.7" "0.15")
(command "_circle" "4156.438,924.7" "0.15")
(command "_circle" "4156.063,924.7" "0.075")
(command "_circle" "4155.688,924.7" "0.15")
(command "_circle" "4157.938,926.7" "0.075")
(command "_circle" "4157.563,926.7" "0.15")
(command "_circle" "4157.188,926.7" "0.075")
(command "_circle" "4156.813,926.7" "0.15")
(command "_circle" "4156.438,926.7" "0.15")
(command "_circle" "4156.063,926.7" "0.075")
(command "_circle" "4155.688,926.7" "0.15")
(command "_circle" "4157.938,928.7" "0.075")
(command "_circle" "4157.563,928.7" "0.075")
(command "_circle" "4157.188,928.7" "0.15")
(command "_circle" "4156.813,928.7" "0.15")
(command "_circle" "4156.438,928.7" "0.15")
(command "_circle" "4156.063,928.7" "0.075")
(command "_circle" "4155.688,928.7" "0.15")
(command "_circle" "4157.938,930.7" "0.075")
(command "_circle" "4157.563,930.7" "0.15")
(command "_circle" "4157.188,930.7" "0.15")
(command "_circle" "4156.813,930.7" "0.15")
(command "_circle" "4156.438,930.7" "0.15")
(command "_circle" "4156.063,930.7" "0.075")
(command "_circle" "4155.688,930.7" "0.15")
(command "_circle" "4157.938,932.7" "0.075")
(command "_circle" "4157.563,932.7" "0.075")
(command "_circle" "4157.188,932.7" "0.075")
(command "_circle" "4156.813,932.7" "0.075")
(command "_circle" "4156.438,932.7" "0.075")
(command "_circle" "4156.063,932.7" "0.15")
(command "_circle" "4155.688,932.7" "0.15")
(command "_circle" "4157.938,934.7" "0.075")
(command "_circle" "4157.563,934.7" "0.15")
(command "_circle" "4157.188,934.7" "0.075")
(command "_circle" "4156.813,934.7" "0.075")
(command "_circle" "4156.438,934.7" "0.075")
(command "_circle" "4156.063,934.7" "0.15")
(command "_circle" "4155.688,934.7" "0.15")
(command "_circle" "4157.938,936.7" "0.075")
(command "_circle" "4157.563,936.7" "0.075")
(command "_circle" "4157.188,936.7" "0.15")
(command "_circle" "4156.813,936.7" "0.075")
(command "_circle" "4156.438,936.7" "0.075")
(command "_circle" "4156.063,936.7" "0.15")
(command "_circle" "4155.688,936.7" "0.15")
(command "_circle" "4157.938,938.7" "0.075")
(command "_circle" "4157.563,938.7" "0.15")
(command "_circle" "4157.188,938.7" "0.15")
(command "_circle" "4156.813,938.7" "0.075")
(command "_circle" "4156.438,938.7" "0.075")
(command "_circle" "4156.063,938.7" "0.15")
(command "_circle" "4155.688,938.7" "0.15")
(command "_circle" "4157.938,940.7" "0.075")
(command "_circle" "4157.563,940.7" "0.075")
(command "_circle" "4157.188,940.7" "0.075")
(command "_circle" "4156.813,940.7" "0.15")
(command "_circle" "4156.438,940.7" "0.075")
(command "_circle" "4156.063,940.7" "0.15")
(command "_circle" "4155.688,940.7" "0.15")
(command "_circle" "4157.938,942.7" "0.075")
(command "_circle" "4157.563,942.7" "0.15")
(command "_circle" "4157.188,942.7" "0.075")
(command "_circle" "4156.813,942.7" "0.15")
(command "_circle" "4156.438,942.7" "0.075")
(command "_circle" "4156.063,942.7" "0.15")
(command "_circle" "4155.688,942.7" "0.15")
(command "_circle" "4157.938,944.7" "0.075")
(command "_circle" "4157.563,944.7" "0.075")
(command "_circle" "4157.188,944.7" "0.15")
(command "_circle" "4156.813,944.7" "0.15")
(command "_circle" "4156.438,944.7" "0.075")
(command "_circle" "4156.063,944.7" "0.15")
(command "_circle" "4155.688,944.7" "0.15")
(command "_circle" "4157.938,946.7" "0.075")
(command "_circle" "4157.563,946.7" "0.15")
(command "_circle" "4157.188,946.7" "0.15")
(command "_circle" "4156.813,946.7" "0.15")
(command "_circle" "4156.438,946.7" "0.075")
(command "_circle" "4156.063,946.7" "0.15")
(command "_circle" "4155.688,946.7" "0.15")
(command "_circle" "4157.938,948.7" "0.075")
(command "_circle" "4157.563,948.7" "0.075")
(command "_circle" "4157.188,948.7" "0.075")
(command "_circle" "4156.813,948.7" "0.075")
(command "_circle" "4156.438,948.7" "0.15")
(command "_circle" "4156.063,948.7" "0.15")
(command "_circle" "4155.688,948.7" "0.15")
(command "_circle" "4157.938,950.7" "0.075")
(command "_circle" "4157.563,950.7" "0.15")
(command "_circle" "4157.188,950.7" "0.075")
(command "_circle" "4156.813,950.7" "0.075")
(command "_circle" "4156.438,950.7" "0.15")
(command "_circle" "4156.063,950.7" "0.15")
(command "_circle" "4155.688,950.7" "0.15")
(command "_circle" "4157.938,952.7" "0.075")
(command "_circle" "4157.563,952.7" "0.075")
(command "_circle" "4157.188,952.7" "0.15")
(command "_circle" "4156.813,952.7" "0.075")
(command "_circle" "4156.438,952.7" "0.15")
(command "_circle" "4156.063,952.7" "0.15")
(command "_circle" "4155.688,952.7" "0.15")
(command "_circle" "4157.938,954.7" "0.075")
(command "_circle" "4157.563,954.7" "0.15")
(command "_circle" "4157.188,954.7" "0.15")
(command "_circle" "4156.813,954.7" "0.075")
(command "_circle" "4156.438,954.7" "0.15")
(command "_circle" "4156.063,954.7" "0.15")
(command "_circle" "4155.688,954.7" "0.15")
(command "_circle" "4157.938,956.7" "0.075")
(command "_circle" "4157.563,956.7" "0.075")
(command "_circle" "4157.188,956.7" "0.075")
(command "_circle" "4156.813,956.7" "0.15")
(command "_circle" "4156.438,956.7" "0.15")
(command "_circle" "4156.063,956.7" "0.15")
(command "_circle" "4155.688,956.7" "0.15")
(command "_circle" "4157.938,958.7" "0.075")
(command "_circle" "4157.563,958.7" "0.15")
(command "_circle" "4157.188,958.7" "0.075")
(command "_circle" "4156.813,958.7" "0.15")
(command "_circle" "4156.438,958.7" "0.15")
(command "_circle" "4156.063,958.7" "0.15")
(command "_circle" "4155.688,958.7" "0.15")
(command "_circle" "4157.938,960.7" "0.075")
(command "_circle" "4157.563,960.7" "0.075")
(command "_circle" "4157.188,960.7" "0.15")
(command "_circle" "4156.813,960.7" "0.15")
(command "_circle" "4156.438,960.7" "0.15")
(command "_circle" "4156.063,960.7" "0.15")
(command "_circle" "4155.688,960.7" "0.15")
(command "_circle" "4157.938,962.7" "0.075")
(command "_circle" "4157.563,962.7" "0.15")
(command "_circle" "4157.188,962.7" "0.15")
(command "_circle" "4156.813,962.7" "0.15")
(command "_circle" "4156.438,962.7" "0.15")
(command "_circle" "4156.063,962.7" "0.15")
(command "_circle" "4155.688,962.7" "0.15")
(command "_layer" "set" "nitride" "")
(command "_layer" "set" "text" "")
(command-s "_text" "4146.888,963.3" "2" "-90" "a = 370 nm" )
(sssetfirst nil (ssget "_L"))
(if (not (numberp (vl-string-search "Mac" (getvar "platform")))) (c:txtexp))
(command "_layer" "set" "nitride" "")
(command "_layer" "set" "text" "")
(command-s "_text" "4143.888,963.3" "2" "-90" "gap = 250 nm" )
(sssetfirst nil (ssget "_L"))
(if (not (numberp (vl-string-search "Mac" (getvar "platform")))) (c:txtexp))
(command "_layer" "set" "nitride" "")
(command "_layer" "set" "text" "")
(command-s "_text" "4140.888,963.3" "2" "-90" "amplitude = 127 nm" )
(sssetfirst nil (ssget "_L"))
(if (not (numberp (vl-string-search "Mac" (getvar "platform")))) (c:txtexp))
(command "_layer" "set" "nitride" "")
(command "_layer" "set" "text" "")
(command-s "_text" "4137.888,963.3" "2" "-90" "start width = 280 nm" )
(sssetfirst nil (ssget "_L"))
(if (not (numberp (vl-string-search "Mac" (getvar "platform")))) (c:txtexp))
(command "_layer" "set" "nitride" "")
(command "_layer" "set" "text" "")
(command-s "_text" "4134.888,963.3" "2" "-90" "width = 304 nm" )
(sssetfirst nil (ssget "_L"))
(if (not (numberp (vl-string-search "Mac" (getvar "platform")))) (c:txtexp))
(command "_layer" "set" "nitride" "")
(command "_layer" "set" "text" "")
(command-s "_text" "4131.888,963.3" "2" "-90" "taper: 15" )
(sssetfirst nil (ssget "_L"))
(if (not (numberp (vl-string-search "Mac" (getvar "platform")))) (c:txtexp))
(command "_layer" "set" "nitride" "")
(command "_layer" "set" "text" "")
(command-s "_text" "4128.888,963.3" "2" "-90" "nominal: 150" )
(sssetfirst nil (ssget "_L"))
(if (not (numberp (vl-string-search "Mac" (getvar "platform")))) (c:txtexp))
(command "_layer" "set" "nitride" "")
(command "_layer" "set" "indicators" "")
(setq coords (list 
(list 4080.415 940) 
(list 4080.415 920) 
(list 4060.415 900) 
(list 4080.415 880) 
(list 4080.415 860) 
(list 4080.415 900) 
(list 4080.415 887.0711) 
(list 4067.4861 900) 
(list 4080.415 912.9289) 
(list 4080.415 900)))
(apply 'command (append '("pline") coords '("c")))
(command "._fillet" "radius" "1" "._fillet" "P" (entlast))
(setq coords (list 
(list 4239.585 940) 
(list 4239.585 920) 
(list 4259.585 900) 
(list 4239.585 880) 
(list 4239.585 860) 
(list 4239.585 900) 
(list 4239.585 887.0711) 
(list 4252.5139 900) 
(list 4239.585 912.9289) 
(list 4239.585 900)))
(apply 'command (append '("pline") coords '("c")))
(command "._fillet" "radius" "1" "._fillet" "P" (entlast))
(command "_layer" "set" "holes" "")
(command "_circle" "4078.0629,914.1124" "0.5")
(command "_circle" "4075.7109,911.7603" "0.5")
(command "_circle" "4073.3588,909.4083" "0.5")
(command "_circle" "4071.0067,907.0562" "0.5")
(command "_circle" "4068.6547,904.7041" "0.5")
(command "_circle" "4066.3026,902.3521" "0.5")
(command "_circle" "4063.9505,900" "0.5")
(command "_circle" "4066.3026,897.6479" "0.5")
(command "_circle" "4068.6547,895.2959" "0.5")
(command "_circle" "4071.0067,892.9438" "0.5")
(command "_circle" "4073.3588,890.5917" "0.5")
(command "_circle" "4075.7109,888.2397" "0.5")
(command "_circle" "4078.0629,885.8876" "0.5")
(command "_circle" "4241.9371,914.1124" "0.5")
(command "_circle" "4244.2891,911.7603" "0.5")
(command "_circle" "4246.6412,909.4083" "0.5")
(command "_circle" "4248.9933,907.0562" "0.5")
(command "_circle" "4251.3453,904.7041" "0.5")
(command "_circle" "4253.6974,902.3521" "0.5")
(command "_circle" "4256.0495,900" "0.5")
(command "_circle" "4253.6974,897.6479" "0.5")
(command "_circle" "4251.3453,895.2959" "0.5")
(command "_circle" "4248.9933,892.9438" "0.5")
(command "_circle" "4246.6412,890.5917" "0.5")
(command "_circle" "4244.2891,888.2397" "0.5")
(command "_circle" "4241.9371,885.8876" "0.5")
(command "_layer" "set" "nitride" "")
(command "_block" "blkcoupler13" "4160,900" coupler13 "")
(command "_insert" "blkcoupler13" "4160,900" "1" "1" "0")
(command "_insert" "blkcoupler13" "4160,900" "1" "1" "180")
(command "_block" "blksinglenanobeam13" "4160,900" singlenanobeam13 "")
(command "_insert" "blksinglenanobeam13" "4160,900" "1" "1" "0")
(command "_insert" "blksinglenanobeam13" "4160,900" "1" "1" "180")
(command "_block" "blkanglednodearray13" "4160,900" anglednodearray13 "")
(command "_insert" "blkanglednodearray13" "4160,900" "1" "1" "0")
(command "_insert" "blkanglednodearray13" "4160,900" "1" "1" "180")
(command "_block" "blkcooledsinglenanobeam13" "4160,900" cooledsinglenanobeam13 "")
(command "_insert" "blkcooledsinglenanobeam13" "4160,900" "1" "1" "0")
(command "_insert" "blkcooledsinglenanobeam13" "4160,900" "1" "1" "180")
(command "_block" "blkyjunction13" "4160,900" yjunction13 "")
(command "_insert" "blkyjunction13" "4160,900" "1" "1" "0")
(command "_insert" "blkyjunction13" "4160,900" "1" "1" "180")
; DRAWING BULGING VEE GROOVE
(command "_layer" "set" "vgroove" "")
(setq coords (list 
(list 4085.415 -605) 
(list 4085.415 0) 
(list 4085.415 0) 
(list 4085.415 1800) 
(list 4085.415 1800) 
(list 4085.415 2405) 
(list 4234.585 2405) 
(list 4234.585 1800) 
(list 4234.585 1800) 
(list 4234.585 0) 
(list 4234.585 0) 
(list 4234.585 -605)))
(apply 'command (append '("pline") coords '("c")))
(command "._fillet" "radius" "0" "._fillet" "P" (entlast))
(command "_layer" "set" "window" "")
(command "_rectangle" "4085.415,-1935" "4234.585,-600")
(command "_rectangle" "4085.415,2400" "4234.585,5300")
(command "_layer" "set" "grid" "")
(command "_rectangle" "4086.415,-1934" "4109.9433,-1909.2133")
(command "_array" "last" "" "R" "75" "3" "25.7867" "24.5283")
(command "_rectangle" "4161,-1934" "4184.5283,-1909.2133")
(command "_array" "last" "" "R" "75" "3" "25.7867" "24.5283")
(command "_rectangle" "4086.415,1" "4109.9433,25.7")
(command "_array" "last" "" "R" "70" "3" "25.7" "24.5283")
(command "_rectangle" "4161,1" "4184.5283,25.7")
(command "_array" "last" "" "R" "70" "3" "25.7" "24.5283")
(command "_rectangle" "4086.415,1801" "4109.9433,1825.9185")
(command "_array" "last" "" "R" "135" "3" "25.9185" "24.5283")
(command "_rectangle" "4161,1801" "4184.5283,1825.9185")
(command "_array" "last" "" "R" "135" "3" "25.9185" "24.5283")
(command "_layer" "set" "vgrooveFDA" "")
(command "_rectangle" "4234.585,-2233" "4085.415,-1933")
(command "_layer" "set" "nitride" "")
(command "_layer" "set" "holes" "")
(command "_circle" "4237.085,331.5" "0.5")
(command "_array" "last" "" "R" "379" "1" "3" "2.5")
(command "_circle" "4082.915,331.5" "0.5")
(command "_array" "last" "" "R" "379" "1" "3" "-2.5")
(command "_layer" "set" "nitride" "")
(command "_layer" "set" "window" "")
(command "_layer" "set" "window" "")
(command "_rectangle" "4239.585,0" "4400.415,1800")
(command "._fillet" "radius" "20" "._fillet" "P" (entlast))
(command "_layer" "set" "grid" "")
(command "_rectangle" "4240.585,1" "4262.4179,25.7")
(command "_array" "last" "" "R" "70" "7" "25.7" "22.8329")
(command "_layer" "set" "nitride" "")
; DRAWING REGION LAYER
(command "_layer" "set" "regionLayer13" "")
(command "_rectangle" "4080,-460" "4240,2260")
(command "_layer" "set" "nitride" "")
(setq coupler13 nil)
(setq singlenanobeam13 nil)
(setq anglednodearray13 nil)
(setq cooledsinglenanobeam13 nil)
(setq yjunction13 nil)
; DEVICE #14
(command "_layer" "set" "window" "")
(command "_circle" "4392.915,-415" "5")
(command "_circle" "4392.915,-402.5" "5")
(command "_circle" "4392.915,-390" "5")
(command "_circle" "4392.915,-377.5" "5")
(command "_circle" "4380.415,-415" "5")
(command "_circle" "4380.415,-402.5" "5")
(command "_circle" "4380.415,-390" "5")
(command "_circle" "4380.415,-377.5" "5")
(command "_circle" "4367.915,-415" "5")
(command "_circle" "4367.915,-402.5" "5")
(command "_circle" "4367.915,-390" "5")
(command "_circle" "4367.915,-377.5" "5")
(command "_circle" "4355.415,-415" "5")
(command "_circle" "4355.415,-402.5" "5")
(command "_layer" "set" "nitride" "")
(setq currobj nil)
(setq currobj (ssadd))
; DRAWING COUPLER
(setq coords (list 
(list 4480.0675 -415) 
(list 4480.0675 -413) 
(list 4553.585 -413) 
(list 4553.585 -413) 
(list 4553.9677 -413.0761) 
(list 4554.2921 -413.2929) 
(list 4554.5089 -413.6173) 
(list 4554.585 -414) 
(list 4554.585 -411.8) 
(list 4554.585 -411.8) 
(list 4554.5089 -412.1827) 
(list 4554.2921 -412.5071) 
(list 4553.9677 -412.7239) 
(list 4553.585 -412.8) 
(list 4480.0675 -412.8) 
(list 4480.0675 -410.8) 
(list 4479.9325 -410.8) 
(list 4479.9325 -412.8) 
(list 4406.415 -412.8) 
(list 4406.0323 -412.7239) 
(list 4405.7079 -412.5071) 
(list 4405.4911 -412.1827) 
(list 4405.415 -411.8) 
(list 4405.415 -411.8) 
(list 4405.415 -414) 
(list 4405.4911 -413.6173) 
(list 4405.7079 -413.2929) 
(list 4406.0323 -413.0761) 
(list 4406.415 -413) 
(list 4406.415 -413) 
(list 4479.9325 -413) 
(list 4479.9325 -415)))
(apply 'command (append '("pline") coords '("c")))
(setq currobj (ssadd (entlast) currobj))
(command "._fillet" "radius" "0.3" "._fillet" "P" (entlast))
(command "_layer" "set" "holes" "")
(command "_circle" "4480,-412.9" "0.113")
(setq currobj (ssadd (entlast) currobj))
(command "_layer" "set" "nitride" "")
(command "_layer" "set" "text" "")
(command "_circle" "4479.2,-415" "0.075")
(command "_circle" "4479.2,-414.7" "0.075")
(command "_circle" "4479.2,-414.4" "0.075")
(command "_circle" "4478.9,-415" "0.075")
(command "_circle" "4478.9,-414.7" "0.075")
(command "_circle" "4478.9,-414.4" "0.075")
(command "_circle" "4478.6,-415" "0.075")
(command "_circle" "4478.6,-414.7" "0.075")
(command "_circle" "4478.6,-414.4" "0.075")
(command "_layer" "set" "nitride" "")
(command "_layer" "set" "prebias" "")
(command "_rectangle" "4405.415,-414" "4554.585,-411.8")
(setq currobj (ssadd (entlast) currobj))
(command "_rectangle" "4479.9325,-415" "4480.0675,-410.8")
(setq currobj (ssadd (entlast) currobj))
(command "_layer" "set" "nitride" "")
(setq coupler14 currobj)
(setq currobj nil)
(setq currobj (ssadd))
; DRAWING SINGLE NANOBEAM
(setq coords (list 
(list 4480.0675 -410.8) 
(list 4480.0675 -409.1417) 
(list 4480.0675 -407.4833) 
(list 4480.0675 -405.825) 
(list 4480.0675 -404.1667) 
(list 4480.0675 -402.5083) 
(list 4480.0675 -400.85) 
(list 4480.0675 -399.1917) 
(list 4480.0675 -397.5333) 
(list 4480.0675 -395.875) 
(list 4480.0676 -394.2167) 
(list 4480.0676 -392.5583) 
(list 4480.0676 -390.9) 
(list 4480.0676 -389.2417) 
(list 4480.0677 -387.5833) 
(list 4480.0677 -385.925) 
(list 4480.0678 -384.2667) 
(list 4480.0678 -382.6083) 
(list 4480.0679 -380.95) 
(list 4480.068 -379.2917) 
(list 4480.068 -377.6333) 
(list 4480.0681 -375.975) 
(list 4480.0682 -374.3167) 
(list 4480.0683 -372.6583) 
(list 4480.0684 -371) 
(list 4480.0686 -369.3417) 
(list 4480.0687 -367.6833) 
(list 4480.0688 -366.025) 
(list 4480.069 -364.3667) 
(list 4480.0692 -362.7083) 
(list 4480.0693 -361.05) 
(list 4480.0695 -359.3917) 
(list 4480.0697 -357.7333) 
(list 4480.0699 -356.075) 
(list 4480.0702 -354.4167) 
(list 4480.0704 -352.7583) 
(list 4480.0707 -351.1) 
(list 4480.0709 -349.4417) 
(list 4480.0712 -347.7833) 
(list 4480.0715 -346.125) 
(list 4480.0719 -344.4667) 
(list 4480.0722 -342.8083) 
(list 4480.0725 -341.15) 
(list 4480.0729 -339.4917) 
(list 4480.0733 -337.8333) 
(list 4480.0737 -336.175) 
(list 4480.0741 -334.5167) 
(list 4480.0746 -332.8583) 
(list 4480.075 -331.2) 
(list 4480.0755 -329.5417) 
(list 4480.076 -327.8833) 
(list 4480.0765 -326.225) 
(list 4480.0771 -324.5667) 
(list 4480.0776 -322.9083) 
(list 4480.0782 -321.25) 
(list 4480.0788 -319.5917) 
(list 4480.0794 -317.9333) 
(list 4480.0801 -316.275) 
(list 4480.0808 -314.6167) 
(list 4480.0815 -312.9583) 
(list 4480.0822 -311.3) 
(list 4480.0829 -309.6417) 
(list 4480.0837 -307.9833) 
(list 4480.0845 -306.325) 
(list 4480.0853 -304.6667) 
(list 4480.0862 -303.0083) 
(list 4480.087 -301.35) 
(list 4480.088 -299.6917) 
(list 4480.0889 -298.0333) 
(list 4480.0898 -296.375) 
(list 4480.0908 -294.7167) 
(list 4480.0918 -293.0583) 
(list 4480.0929 -291.4) 
(list 4480.094 -289.7417) 
(list 4480.0951 -288.0833) 
(list 4480.0962 -286.425) 
(list 4480.0973 -284.7667) 
(list 4480.0985 -283.1083) 
(list 4480.0998 -281.45) 
(list 4480.101 -279.7917) 
(list 4480.1023 -278.1333) 
(list 4480.1036 -276.475) 
(list 4480.105 -274.8167) 
(list 4480.1064 -273.1583) 
(list 4480.1078 -271.5) 
(list 4480.1093 -269.8417) 
(list 4480.1107 -268.1833) 
(list 4480.1123 -266.525) 
(list 4480.1138 -264.8667) 
(list 4480.1154 -263.2083) 
(list 4480.1171 -261.55) 
(list 4480.1187 -259.8917) 
(list 4480.1204 -258.2333) 
(list 4480.1222 -256.575) 
(list 4480.124 -254.9167) 
(list 4480.1258 -253.2583) 
(list 4480.1277 -251.6) 
(list 4480.1296 -249.9417) 
(list 4480.1315 -248.2833) 
(list 4480.1335 -246.625) 
(list 4480.1355 -244.9667) 
(list 4480.1376 -243.3083) 
(list 4480.1397 -241.65) 
(list 4480.1418 -239.9917) 
(list 4480.144 -238.3333) 
(list 4480.1462 -236.675) 
(list 4480.1485 -235.0167) 
(list 4480.1508 -233.3583) 
(list 4480.1532 -231.7) 
(list 4480.1556 -230.0417) 
(list 4480.158 -228.3833) 
(list 4480.1605 -226.725) 
(list 4480.163 -225.0667) 
(list 4480.1656 -223.4083) 
(list 4480.1682 -221.75) 
(list 4480.1709 -220.0917) 
(list 4480.1736 -218.4333) 
(list 4480.1764 -216.775) 
(list 4480.1792 -215.1167) 
(list 4480.1821 -213.4583) 
(list 4480.185 -211.8) 
(list 4479.815 -211.8) 
(list 4479.8179 -213.4583) 
(list 4479.8208 -215.1167) 
(list 4479.8236 -216.775) 
(list 4479.8264 -218.4333) 
(list 4479.8291 -220.0917) 
(list 4479.8318 -221.75) 
(list 4479.8344 -223.4083) 
(list 4479.837 -225.0667) 
(list 4479.8395 -226.725) 
(list 4479.842 -228.3833) 
(list 4479.8444 -230.0417) 
(list 4479.8468 -231.7) 
(list 4479.8492 -233.3583) 
(list 4479.8515 -235.0167) 
(list 4479.8538 -236.675) 
(list 4479.856 -238.3333) 
(list 4479.8582 -239.9917) 
(list 4479.8603 -241.65) 
(list 4479.8624 -243.3083) 
(list 4479.8645 -244.9667) 
(list 4479.8665 -246.625) 
(list 4479.8685 -248.2833) 
(list 4479.8704 -249.9417) 
(list 4479.8723 -251.6) 
(list 4479.8742 -253.2583) 
(list 4479.876 -254.9167) 
(list 4479.8778 -256.575) 
(list 4479.8796 -258.2333) 
(list 4479.8813 -259.8917) 
(list 4479.8829 -261.55) 
(list 4479.8846 -263.2083) 
(list 4479.8862 -264.8667) 
(list 4479.8877 -266.525) 
(list 4479.8893 -268.1833) 
(list 4479.8907 -269.8417) 
(list 4479.8922 -271.5) 
(list 4479.8936 -273.1583) 
(list 4479.895 -274.8167) 
(list 4479.8964 -276.475) 
(list 4479.8977 -278.1333) 
(list 4479.899 -279.7917) 
(list 4479.9002 -281.45) 
(list 4479.9015 -283.1083) 
(list 4479.9027 -284.7667) 
(list 4479.9038 -286.425) 
(list 4479.9049 -288.0833) 
(list 4479.906 -289.7417) 
(list 4479.9071 -291.4) 
(list 4479.9082 -293.0583) 
(list 4479.9092 -294.7167) 
(list 4479.9102 -296.375) 
(list 4479.9111 -298.0333) 
(list 4479.912 -299.6917) 
(list 4479.913 -301.35) 
(list 4479.9138 -303.0083) 
(list 4479.9147 -304.6667) 
(list 4479.9155 -306.325) 
(list 4479.9163 -307.9833) 
(list 4479.9171 -309.6417) 
(list 4479.9178 -311.3) 
(list 4479.9185 -312.9583) 
(list 4479.9192 -314.6167) 
(list 4479.9199 -316.275) 
(list 4479.9206 -317.9333) 
(list 4479.9212 -319.5917) 
(list 4479.9218 -321.25) 
(list 4479.9224 -322.9083) 
(list 4479.9229 -324.5667) 
(list 4479.9235 -326.225) 
(list 4479.924 -327.8833) 
(list 4479.9245 -329.5417) 
(list 4479.925 -331.2) 
(list 4479.9254 -332.8583) 
(list 4479.9259 -334.5167) 
(list 4479.9263 -336.175) 
(list 4479.9267 -337.8333) 
(list 4479.9271 -339.4917) 
(list 4479.9275 -341.15) 
(list 4479.9278 -342.8083) 
(list 4479.9281 -344.4667) 
(list 4479.9285 -346.125) 
(list 4479.9288 -347.7833) 
(list 4479.9291 -349.4417) 
(list 4479.9293 -351.1) 
(list 4479.9296 -352.7583) 
(list 4479.9298 -354.4167) 
(list 4479.9301 -356.075) 
(list 4479.9303 -357.7333) 
(list 4479.9305 -359.3917) 
(list 4479.9307 -361.05) 
(list 4479.9308 -362.7083) 
(list 4479.931 -364.3667) 
(list 4479.9312 -366.025) 
(list 4479.9313 -367.6833) 
(list 4479.9314 -369.3417) 
(list 4479.9316 -371) 
(list 4479.9317 -372.6583) 
(list 4479.9318 -374.3167) 
(list 4479.9319 -375.975) 
(list 4479.932 -377.6333) 
(list 4479.932 -379.2917) 
(list 4479.9321 -380.95) 
(list 4479.9322 -382.6083) 
(list 4479.9322 -384.2667) 
(list 4479.9323 -385.925) 
(list 4479.9323 -387.5833) 
(list 4479.9324 -389.2417) 
(list 4479.9324 -390.9) 
(list 4479.9324 -392.5583) 
(list 4479.9324 -394.2167) 
(list 4479.9325 -395.875) 
(list 4479.9325 -397.5333) 
(list 4479.9325 -399.1917) 
(list 4479.9325 -400.85) 
(list 4479.9325 -402.5083) 
(list 4479.9325 -404.1667) 
(list 4479.9325 -405.825) 
(list 4479.9325 -407.4833) 
(list 4479.9325 -409.1417) 
(list 4479.9325 -410.8)))
(apply 'command (append '("pline") coords '("c")))
(setq currobj (ssadd (entlast) currobj))
(command "_layer" "set" "prebias" "")
(command "_rectangle" "4479.815,-410.8" "4480.185,-211.8")
(setq currobj (ssadd (entlast) currobj))
(command "_layer" "set" "nitride" "")
(setq singlenanobeam14 currobj)
(setq currobj nil)
(setq currobj (ssadd))
; DRAWING NODE ARRAY
(setq coords (list 
(list 4480.185 -211.8) 
(list 4480.5625 -201.8) 
(list 4480.5625 -201.8) 
(list 4480.5625 -200.8) 
(list 4554.585 -212.6864) 
(list 4554.585 -207.7434) 
(list 4480.5625 -197.357) 
(list 4480.5625 -196.357) 
(list 4480.5625 -196.357) 
(list 4480.2625 -186.357) 
(list 4479.7375 -186.357) 
(list 4479.4375 -196.357) 
(list 4479.4375 -196.357) 
(list 4479.4375 -197.357) 
(list 4405.415 -207.7434) 
(list 4405.415 -212.6864) 
(list 4479.4375 -200.8) 
(list 4479.4375 -201.8) 
(list 4479.4375 -201.8) 
(list 4479.815 -211.8)))
(apply 'command (append '("pline") coords '("c")))
(setq currobj (ssadd (entlast) currobj))
(command "_layer" "set" "prebias" "")
(setq coords (list 
(list 4479.4375 -212.6864) 
(list 4479.4375 -200.8) 
(list 4405.415 -212.6864) 
(list 4405.415 -207.7434) 
(list 4479.4375 -197.357) 
(list 4479.4375 -186.357) 
(list 4480.5625 -186.357) 
(list 4480.5625 -197.357) 
(list 4554.585 -207.7434) 
(list 4554.585 -212.6864) 
(list 4480.5625 -200.8) 
(list 4480.5625 -212.6864)))
(apply 'command (append '("pline") coords '("c")))
(setq currobj (ssadd (entlast) currobj))
(command "_layer" "set" "nitride" "")
(command "_layer" "set" "fda1" "")
(setq coords (list 
(list 4480.5625 -200.657) 
(list 4554.585 -212.5434) 
(list 4554.585 -212.3664) 
(list 4480.5625 -200.58)))
(apply 'command (append '("pline") coords '("c")))
(setq currobj (ssadd (entlast) currobj))
(setq coords (list 
(list 4480.5625 -200.437) 
(list 4554.585 -212.2234) 
(list 4554.585 -212.0464) 
(list 4480.5625 -200.36)))
(apply 'command (append '("pline") coords '("c")))
(setq currobj (ssadd (entlast) currobj))
(setq coords (list 
(list 4480.5625 -200.217) 
(list 4554.585 -211.9034) 
(list 4554.585 -211.7264) 
(list 4480.5625 -200.14)))
(apply 'command (append '("pline") coords '("c")))
(setq currobj (ssadd (entlast) currobj))
(setq coords (list 
(list 4480.5625 -199.997) 
(list 4554.585 -211.5834) 
(list 4554.585 -211.4064) 
(list 4480.5625 -199.92)))
(apply 'command (append '("pline") coords '("c")))
(setq currobj (ssadd (entlast) currobj))
(setq coords (list 
(list 4480.5625 -199.777) 
(list 4554.585 -211.2634) 
(list 4554.585 -211.0864) 
(list 4480.5625 -199.7)))
(apply 'command (append '("pline") coords '("c")))
(setq currobj (ssadd (entlast) currobj))
(setq coords (list 
(list 4480.5625 -199.557) 
(list 4554.585 -210.9434) 
(list 4554.585 -210.7664) 
(list 4480.5625 -199.48)))
(apply 'command (append '("pline") coords '("c")))
(setq currobj (ssadd (entlast) currobj))
(setq coords (list 
(list 4480.5625 -199.337) 
(list 4554.585 -210.6234) 
(list 4554.585 -210.4464) 
(list 4480.5625 -199.26)))
(apply 'command (append '("pline") coords '("c")))
(setq currobj (ssadd (entlast) currobj))
(setq coords (list 
(list 4480.5625 -199.117) 
(list 4554.585 -210.3034) 
(list 4554.585 -210.1264) 
(list 4480.5625 -199.04)))
(apply 'command (append '("pline") coords '("c")))
(setq currobj (ssadd (entlast) currobj))
(setq coords (list 
(list 4480.5625 -198.897) 
(list 4554.585 -209.9834) 
(list 4554.585 -209.8064) 
(list 4480.5625 -198.82)))
(apply 'command (append '("pline") coords '("c")))
(setq currobj (ssadd (entlast) currobj))
(setq coords (list 
(list 4480.5625 -198.677) 
(list 4554.585 -209.6634) 
(list 4554.585 -209.4864) 
(list 4480.5625 -198.6)))
(apply 'command (append '("pline") coords '("c")))
(setq currobj (ssadd (entlast) currobj))
(setq coords (list 
(list 4480.5625 -198.457) 
(list 4554.585 -209.3434) 
(list 4554.585 -209.1664) 
(list 4480.5625 -198.38)))
(apply 'command (append '("pline") coords '("c")))
(setq currobj (ssadd (entlast) currobj))
(setq coords (list 
(list 4480.5625 -198.237) 
(list 4554.585 -209.0234) 
(list 4554.585 -208.8464) 
(list 4480.5625 -198.16)))
(apply 'command (append '("pline") coords '("c")))
(setq currobj (ssadd (entlast) currobj))
(setq coords (list 
(list 4480.5625 -198.017) 
(list 4554.585 -208.7034) 
(list 4554.585 -208.5264) 
(list 4480.5625 -197.94)))
(apply 'command (append '("pline") coords '("c")))
(setq currobj (ssadd (entlast) currobj))
(setq coords (list 
(list 4480.5625 -197.797) 
(list 4554.585 -208.3834) 
(list 4554.585 -208.2064) 
(list 4480.5625 -197.72)))
(apply 'command (append '("pline") coords '("c")))
(setq currobj (ssadd (entlast) currobj))
(setq coords (list 
(list 4480.5625 -197.577) 
(list 4554.585 -208.0634) 
(list 4554.585 -207.8864) 
(list 4480.5625 -197.5)))
(apply 'command (append '("pline") coords '("c")))
(setq currobj (ssadd (entlast) currobj))
(setq coords (list 
(list 4479.4375 -197.5) 
(list 4405.415 -207.8864) 
(list 4405.415 -208.0634) 
(list 4479.4375 -197.577)))
(apply 'command (append '("pline") coords '("c")))
(setq currobj (ssadd (entlast) currobj))
(setq coords (list 
(list 4479.4375 -197.72) 
(list 4405.415 -208.2064) 
(list 4405.415 -208.3834) 
(list 4479.4375 -197.797)))
(apply 'command (append '("pline") coords '("c")))
(setq currobj (ssadd (entlast) currobj))
(setq coords (list 
(list 4479.4375 -197.94) 
(list 4405.415 -208.5264) 
(list 4405.415 -208.7034) 
(list 4479.4375 -198.017)))
(apply 'command (append '("pline") coords '("c")))
(setq currobj (ssadd (entlast) currobj))
(setq coords (list 
(list 4479.4375 -198.16) 
(list 4405.415 -208.8464) 
(list 4405.415 -209.0234) 
(list 4479.4375 -198.237)))
(apply 'command (append '("pline") coords '("c")))
(setq currobj (ssadd (entlast) currobj))
(setq coords (list 
(list 4479.4375 -198.38) 
(list 4405.415 -209.1664) 
(list 4405.415 -209.3434) 
(list 4479.4375 -198.457)))
(apply 'command (append '("pline") coords '("c")))
(setq currobj (ssadd (entlast) currobj))
(setq coords (list 
(list 4479.4375 -198.6) 
(list 4405.415 -209.4864) 
(list 4405.415 -209.6634) 
(list 4479.4375 -198.677)))
(apply 'command (append '("pline") coords '("c")))
(setq currobj (ssadd (entlast) currobj))
(setq coords (list 
(list 4479.4375 -198.82) 
(list 4405.415 -209.8064) 
(list 4405.415 -209.9834) 
(list 4479.4375 -198.897)))
(apply 'command (append '("pline") coords '("c")))
(setq currobj (ssadd (entlast) currobj))
(setq coords (list 
(list 4479.4375 -199.04) 
(list 4405.415 -210.1264) 
(list 4405.415 -210.3034) 
(list 4479.4375 -199.117)))
(apply 'command (append '("pline") coords '("c")))
(setq currobj (ssadd (entlast) currobj))
(setq coords (list 
(list 4479.4375 -199.26) 
(list 4405.415 -210.4464) 
(list 4405.415 -210.6234) 
(list 4479.4375 -199.337)))
(apply 'command (append '("pline") coords '("c")))
(setq currobj (ssadd (entlast) currobj))
(setq coords (list 
(list 4479.4375 -199.48) 
(list 4405.415 -210.7664) 
(list 4405.415 -210.9434) 
(list 4479.4375 -199.557)))
(apply 'command (append '("pline") coords '("c")))
(setq currobj (ssadd (entlast) currobj))
(setq coords (list 
(list 4479.4375 -199.7) 
(list 4405.415 -211.0864) 
(list 4405.415 -211.2634) 
(list 4479.4375 -199.777)))
(apply 'command (append '("pline") coords '("c")))
(setq currobj (ssadd (entlast) currobj))
(setq coords (list 
(list 4479.4375 -199.92) 
(list 4405.415 -211.4064) 
(list 4405.415 -211.5834) 
(list 4479.4375 -199.997)))
(apply 'command (append '("pline") coords '("c")))
(setq currobj (ssadd (entlast) currobj))
(setq coords (list 
(list 4479.4375 -200.14) 
(list 4405.415 -211.7264) 
(list 4405.415 -211.9034) 
(list 4479.4375 -200.217)))
(apply 'command (append '("pline") coords '("c")))
(setq currobj (ssadd (entlast) currobj))
(setq coords (list 
(list 4479.4375 -200.36) 
(list 4405.415 -212.0464) 
(list 4405.415 -212.2234) 
(list 4479.4375 -200.437)))
(apply 'command (append '("pline") coords '("c")))
(setq currobj (ssadd (entlast) currobj))
(setq coords (list 
(list 4479.4375 -200.58) 
(list 4405.415 -212.3664) 
(list 4405.415 -212.5434) 
(list 4479.4375 -200.657)))
(apply 'command (append '("pline") coords '("c")))
(setq currobj (ssadd (entlast) currobj))
(command "_layer" "set" "nitride" "")
(command "_layer" "set" "text" "")
(command "_circle" "4478.985,-211.8" "0.075")
(command "_circle" "4478.985,-211.5" "0.075")
(command "_circle" "4478.985,-211.2" "0.075")
(command "_circle" "4478.985,-210.9" "0.075")
(command "_circle" "4478.985,-210.6" "0.075")
(command "_circle" "4478.685,-211.8" "0.075")
(command "_circle" "4478.685,-211.5" "0.075")
(command "_circle" "4478.685,-211.2" "0.075")
(command "_circle" "4478.685,-210.9" "0.075")
(command "_circle" "4478.685,-210.6" "0.075")
(command "_circle" "4478.385,-211.8" "0.075")
(command "_circle" "4478.385,-211.5" "0.075")
(command "_circle" "4478.385,-211.2" "0.075")
(command "_circle" "4478.385,-210.9" "0.075")
(command "_circle" "4478.385,-210.6" "0.075")
(command "_circle" "4478.085,-211.8" "0.075")
(command "_circle" "4478.085,-211.5" "0.075")
(command "_circle" "4478.085,-211.2" "0.075")
(command "_circle" "4478.085,-210.9" "0.075")
(command "_circle" "4478.085,-210.6" "0.075")
(command "_circle" "4477.785,-211.8" "0.075")
(command "_circle" "4477.785,-211.5" "0.075")
(command "_circle" "4477.785,-211.2" "0.075")
(command "_circle" "4477.785,-210.9" "0.075")
(command "_circle" "4477.785,-210.6" "0.075")
(command "_layer" "set" "nitride" "")
(setq anglednodearray14 currobj)
(setq currobj nil)
(setq currobj (ssadd))
; DRAWING COOLED SINGLE NANOBEAM
(setq coords (list 
(list 4480.2625 -186.357) 
(list 4480.2625 -181.357) 
(list 4479.7375 -181.357) 
(list 4479.7375 -186.357)))
(apply 'command (append '("pline") coords '("c")))
(setq currobj (ssadd (entlast) currobj))
(command "_layer" "set" "prebias" "")
(command "_rectangle" "4479.7375,-186.357" "4480.2625,-181.357")
(setq currobj (ssadd (entlast) currobj))
(command "_layer" "set" "nitride" "")
(setq coords (list 
(list 4480.2625 -181.357) 
(list 4480.5625 -171.357) 
(list 4480.5625 -171.357) 
(list 4480.5625 -170.357) 
(list 4554.585 -171.107) 
(list 4554.585 -166.164) 
(list 4480.5625 -166.914) 
(list 4480.5625 -165.914) 
(list 4480.5625 -165.914) 
(list 4480.2625 -155.914) 
(list 4479.7375 -155.914) 
(list 4479.4375 -165.914) 
(list 4479.4375 -165.914) 
(list 4479.4375 -166.914) 
(list 4405.415 -166.164) 
(list 4405.415 -171.107) 
(list 4479.4375 -170.357) 
(list 4479.4375 -171.357) 
(list 4479.4375 -171.357) 
(list 4479.7375 -181.357)))
(apply 'command (append '("pline") coords '("c")))
(setq currobj (ssadd (entlast) currobj))
(command "_layer" "set" "prebias" "")
(setq coords (list 
(list 4479.4375 -181.357) 
(list 4479.4375 -170.357) 
(list 4405.415 -171.107) 
(list 4405.415 -166.164) 
(list 4479.4375 -166.914) 
(list 4479.4375 -155.914) 
(list 4480.5625 -155.914) 
(list 4480.5625 -166.914) 
(list 4554.585 -166.164) 
(list 4554.585 -171.107) 
(list 4480.5625 -170.357) 
(list 4480.5625 -181.357)))
(apply 'command (append '("pline") coords '("c")))
(setq currobj (ssadd (entlast) currobj))
(command "_layer" "set" "nitride" "")
(command "_layer" "set" "fda1" "")
(setq coords (list 
(list 4480.5625 -170.214) 
(list 4554.585 -170.964) 
(list 4554.585 -170.787) 
(list 4480.5625 -170.137)))
(apply 'command (append '("pline") coords '("c")))
(setq currobj (ssadd (entlast) currobj))
(setq coords (list 
(list 4480.5625 -169.994) 
(list 4554.585 -170.644) 
(list 4554.585 -170.467) 
(list 4480.5625 -169.917)))
(apply 'command (append '("pline") coords '("c")))
(setq currobj (ssadd (entlast) currobj))
(setq coords (list 
(list 4480.5625 -169.774) 
(list 4554.585 -170.324) 
(list 4554.585 -170.147) 
(list 4480.5625 -169.697)))
(apply 'command (append '("pline") coords '("c")))
(setq currobj (ssadd (entlast) currobj))
(setq coords (list 
(list 4480.5625 -169.554) 
(list 4554.585 -170.004) 
(list 4554.585 -169.827) 
(list 4480.5625 -169.477)))
(apply 'command (append '("pline") coords '("c")))
(setq currobj (ssadd (entlast) currobj))
(setq coords (list 
(list 4480.5625 -169.334) 
(list 4554.585 -169.684) 
(list 4554.585 -169.507) 
(list 4480.5625 -169.257)))
(apply 'command (append '("pline") coords '("c")))
(setq currobj (ssadd (entlast) currobj))
(setq coords (list 
(list 4480.5625 -169.114) 
(list 4554.585 -169.364) 
(list 4554.585 -169.187) 
(list 4480.5625 -169.037)))
(apply 'command (append '("pline") coords '("c")))
(setq currobj (ssadd (entlast) currobj))
(setq coords (list 
(list 4480.5625 -168.894) 
(list 4554.585 -169.044) 
(list 4554.585 -168.867) 
(list 4480.5625 -168.817)))
(apply 'command (append '("pline") coords '("c")))
(setq currobj (ssadd (entlast) currobj))
(setq coords (list 
(list 4480.5625 -168.674) 
(list 4554.585 -168.724) 
(list 4554.585 -168.547) 
(list 4480.5625 -168.597)))
(apply 'command (append '("pline") coords '("c")))
(setq currobj (ssadd (entlast) currobj))
(setq coords (list 
(list 4480.5625 -168.454) 
(list 4554.585 -168.404) 
(list 4554.585 -168.227) 
(list 4480.5625 -168.377)))
(apply 'command (append '("pline") coords '("c")))
(setq currobj (ssadd (entlast) currobj))
(setq coords (list 
(list 4480.5625 -168.234) 
(list 4554.585 -168.084) 
(list 4554.585 -167.907) 
(list 4480.5625 -168.157)))
(apply 'command (append '("pline") coords '("c")))
(setq currobj (ssadd (entlast) currobj))
(setq coords (list 
(list 4480.5625 -168.014) 
(list 4554.585 -167.764) 
(list 4554.585 -167.587) 
(list 4480.5625 -167.937)))
(apply 'command (append '("pline") coords '("c")))
(setq currobj (ssadd (entlast) currobj))
(setq coords (list 
(list 4480.5625 -167.794) 
(list 4554.585 -167.444) 
(list 4554.585 -167.267) 
(list 4480.5625 -167.717)))
(apply 'command (append '("pline") coords '("c")))
(setq currobj (ssadd (entlast) currobj))
(setq coords (list 
(list 4480.5625 -167.574) 
(list 4554.585 -167.124) 
(list 4554.585 -166.947) 
(list 4480.5625 -167.497)))
(apply 'command (append '("pline") coords '("c")))
(setq currobj (ssadd (entlast) currobj))
(setq coords (list 
(list 4480.5625 -167.354) 
(list 4554.585 -166.804) 
(list 4554.585 -166.627) 
(list 4480.5625 -167.277)))
(apply 'command (append '("pline") coords '("c")))
(setq currobj (ssadd (entlast) currobj))
(setq coords (list 
(list 4480.5625 -167.134) 
(list 4554.585 -166.484) 
(list 4554.585 -166.307) 
(list 4480.5625 -167.057)))
(apply 'command (append '("pline") coords '("c")))
(setq currobj (ssadd (entlast) currobj))
(setq coords (list 
(list 4479.4375 -167.057) 
(list 4405.415 -166.307) 
(list 4405.415 -166.484) 
(list 4479.4375 -167.134)))
(apply 'command (append '("pline") coords '("c")))
(setq currobj (ssadd (entlast) currobj))
(setq coords (list 
(list 4479.4375 -167.277) 
(list 4405.415 -166.627) 
(list 4405.415 -166.804) 
(list 4479.4375 -167.354)))
(apply 'command (append '("pline") coords '("c")))
(setq currobj (ssadd (entlast) currobj))
(setq coords (list 
(list 4479.4375 -167.497) 
(list 4405.415 -166.947) 
(list 4405.415 -167.124) 
(list 4479.4375 -167.574)))
(apply 'command (append '("pline") coords '("c")))
(setq currobj (ssadd (entlast) currobj))
(setq coords (list 
(list 4479.4375 -167.717) 
(list 4405.415 -167.267) 
(list 4405.415 -167.444) 
(list 4479.4375 -167.794)))
(apply 'command (append '("pline") coords '("c")))
(setq currobj (ssadd (entlast) currobj))
(setq coords (list 
(list 4479.4375 -167.937) 
(list 4405.415 -167.587) 
(list 4405.415 -167.764) 
(list 4479.4375 -168.014)))
(apply 'command (append '("pline") coords '("c")))
(setq currobj (ssadd (entlast) currobj))
(setq coords (list 
(list 4479.4375 -168.157) 
(list 4405.415 -167.907) 
(list 4405.415 -168.084) 
(list 4479.4375 -168.234)))
(apply 'command (append '("pline") coords '("c")))
(setq currobj (ssadd (entlast) currobj))
(setq coords (list 
(list 4479.4375 -168.377) 
(list 4405.415 -168.227) 
(list 4405.415 -168.404) 
(list 4479.4375 -168.454)))
(apply 'command (append '("pline") coords '("c")))
(setq currobj (ssadd (entlast) currobj))
(setq coords (list 
(list 4479.4375 -168.597) 
(list 4405.415 -168.547) 
(list 4405.415 -168.724) 
(list 4479.4375 -168.674)))
(apply 'command (append '("pline") coords '("c")))
(setq currobj (ssadd (entlast) currobj))
(setq coords (list 
(list 4479.4375 -168.817) 
(list 4405.415 -168.867) 
(list 4405.415 -169.044) 
(list 4479.4375 -168.894)))
(apply 'command (append '("pline") coords '("c")))
(setq currobj (ssadd (entlast) currobj))
(setq coords (list 
(list 4479.4375 -169.037) 
(list 4405.415 -169.187) 
(list 4405.415 -169.364) 
(list 4479.4375 -169.114)))
(apply 'command (append '("pline") coords '("c")))
(setq currobj (ssadd (entlast) currobj))
(setq coords (list 
(list 4479.4375 -169.257) 
(list 4405.415 -169.507) 
(list 4405.415 -169.684) 
(list 4479.4375 -169.334)))
(apply 'command (append '("pline") coords '("c")))
(setq currobj (ssadd (entlast) currobj))
(setq coords (list 
(list 4479.4375 -169.477) 
(list 4405.415 -169.827) 
(list 4405.415 -170.004) 
(list 4479.4375 -169.554)))
(apply 'command (append '("pline") coords '("c")))
(setq currobj (ssadd (entlast) currobj))
(setq coords (list 
(list 4479.4375 -169.697) 
(list 4405.415 -170.147) 
(list 4405.415 -170.324) 
(list 4479.4375 -169.774)))
(apply 'command (append '("pline") coords '("c")))
(setq currobj (ssadd (entlast) currobj))
(setq coords (list 
(list 4479.4375 -169.917) 
(list 4405.415 -170.467) 
(list 4405.415 -170.644) 
(list 4479.4375 -169.994)))
(apply 'command (append '("pline") coords '("c")))
(setq currobj (ssadd (entlast) currobj))
(setq coords (list 
(list 4479.4375 -170.137) 
(list 4405.415 -170.787) 
(list 4405.415 -170.964) 
(list 4479.4375 -170.214)))
(apply 'command (append '("pline") coords '("c")))
(setq currobj (ssadd (entlast) currobj))
(command "_layer" "set" "nitride" "")
(command "_layer" "set" "text" "")
(command "_circle" "4479.0625,-181.357" "0.075")
(command "_circle" "4479.0625,-181.057" "0.075")
(command "_circle" "4479.0625,-180.757" "0.075")
(command "_circle" "4479.0625,-180.457" "0.075")
(command "_circle" "4479.0625,-180.157" "0.075")
(command "_circle" "4478.7625,-181.357" "0.075")
(command "_circle" "4478.7625,-181.057" "0.075")
(command "_circle" "4478.7625,-180.757" "0.075")
(command "_circle" "4478.7625,-180.457" "0.075")
(command "_circle" "4478.7625,-180.157" "0.075")
(command "_circle" "4478.4625,-181.357" "0.075")
(command "_circle" "4478.4625,-181.057" "0.075")
(command "_circle" "4478.4625,-180.757" "0.075")
(command "_circle" "4478.4625,-180.457" "0.075")
(command "_circle" "4478.4625,-180.157" "0.075")
(command "_circle" "4478.1625,-181.357" "0.075")
(command "_circle" "4478.1625,-181.057" "0.075")
(command "_circle" "4478.1625,-180.757" "0.075")
(command "_circle" "4478.1625,-180.457" "0.075")
(command "_circle" "4478.1625,-180.157" "0.075")
(command "_circle" "4477.8625,-181.357" "0.075")
(command "_circle" "4477.8625,-181.057" "0.075")
(command "_circle" "4477.8625,-180.757" "0.075")
(command "_circle" "4477.8625,-180.457" "0.075")
(command "_circle" "4477.8625,-180.157" "0.075")
(command "_layer" "set" "nitride" "")
(setq coords (list 
(list 4480.2625 -155.914) 
(list 4480.2625 -40.2693) 
(list 4479.7375 -40.2693) 
(list 4479.7375 -155.914)))
(apply 'command (append '("pline") coords '("c")))
(setq currobj (ssadd (entlast) currobj))
(command "_layer" "set" "prebias" "")
(command "_rectangle" "4479.7375,-155.914" "4480.2625,-40.2693")
(setq currobj (ssadd (entlast) currobj))
(command "_layer" "set" "nitride" "")
(setq coords (list 
(list 4480.2625 -40.2693) 
(list 4480.5625 -30.2693) 
(list 4480.5625 -30.2693) 
(list 4480.5625 -29.2693) 
(list 4554.585 -30.0193) 
(list 4554.585 -25.0763) 
(list 4480.5625 -25.8263) 
(list 4480.5625 -24.8263) 
(list 4480.5625 -24.8263) 
(list 4480.2625 -14.8263) 
(list 4479.7375 -14.8263) 
(list 4479.4375 -24.8263) 
(list 4479.4375 -24.8263) 
(list 4479.4375 -25.8263) 
(list 4405.415 -25.0763) 
(list 4405.415 -30.0193) 
(list 4479.4375 -29.2693) 
(list 4479.4375 -30.2693) 
(list 4479.4375 -30.2693) 
(list 4479.7375 -40.2693)))
(apply 'command (append '("pline") coords '("c")))
(setq currobj (ssadd (entlast) currobj))
(command "_layer" "set" "prebias" "")
(setq coords (list 
(list 4479.4375 -40.2693) 
(list 4479.4375 -29.2693) 
(list 4405.415 -30.0193) 
(list 4405.415 -25.0763) 
(list 4479.4375 -25.8263) 
(list 4479.4375 -14.8263) 
(list 4480.5625 -14.8263) 
(list 4480.5625 -25.8263) 
(list 4554.585 -25.0763) 
(list 4554.585 -30.0193) 
(list 4480.5625 -29.2693) 
(list 4480.5625 -40.2693)))
(apply 'command (append '("pline") coords '("c")))
(setq currobj (ssadd (entlast) currobj))
(command "_layer" "set" "nitride" "")
(command "_layer" "set" "fda1" "")
(setq coords (list 
(list 4480.5625 -29.1263) 
(list 4554.585 -29.8763) 
(list 4554.585 -29.6993) 
(list 4480.5625 -29.0493)))
(apply 'command (append '("pline") coords '("c")))
(setq currobj (ssadd (entlast) currobj))
(setq coords (list 
(list 4480.5625 -28.9063) 
(list 4554.585 -29.5563) 
(list 4554.585 -29.3793) 
(list 4480.5625 -28.8293)))
(apply 'command (append '("pline") coords '("c")))
(setq currobj (ssadd (entlast) currobj))
(setq coords (list 
(list 4480.5625 -28.6863) 
(list 4554.585 -29.2363) 
(list 4554.585 -29.0593) 
(list 4480.5625 -28.6093)))
(apply 'command (append '("pline") coords '("c")))
(setq currobj (ssadd (entlast) currobj))
(setq coords (list 
(list 4480.5625 -28.4663) 
(list 4554.585 -28.9163) 
(list 4554.585 -28.7393) 
(list 4480.5625 -28.3893)))
(apply 'command (append '("pline") coords '("c")))
(setq currobj (ssadd (entlast) currobj))
(setq coords (list 
(list 4480.5625 -28.2463) 
(list 4554.585 -28.5963) 
(list 4554.585 -28.4193) 
(list 4480.5625 -28.1693)))
(apply 'command (append '("pline") coords '("c")))
(setq currobj (ssadd (entlast) currobj))
(setq coords (list 
(list 4480.5625 -28.0263) 
(list 4554.585 -28.2763) 
(list 4554.585 -28.0993) 
(list 4480.5625 -27.9493)))
(apply 'command (append '("pline") coords '("c")))
(setq currobj (ssadd (entlast) currobj))
(setq coords (list 
(list 4480.5625 -27.8063) 
(list 4554.585 -27.9563) 
(list 4554.585 -27.7793) 
(list 4480.5625 -27.7293)))
(apply 'command (append '("pline") coords '("c")))
(setq currobj (ssadd (entlast) currobj))
(setq coords (list 
(list 4480.5625 -27.5863) 
(list 4554.585 -27.6363) 
(list 4554.585 -27.4593) 
(list 4480.5625 -27.5093)))
(apply 'command (append '("pline") coords '("c")))
(setq currobj (ssadd (entlast) currobj))
(setq coords (list 
(list 4480.5625 -27.3663) 
(list 4554.585 -27.3163) 
(list 4554.585 -27.1393) 
(list 4480.5625 -27.2893)))
(apply 'command (append '("pline") coords '("c")))
(setq currobj (ssadd (entlast) currobj))
(setq coords (list 
(list 4480.5625 -27.1463) 
(list 4554.585 -26.9963) 
(list 4554.585 -26.8193) 
(list 4480.5625 -27.0693)))
(apply 'command (append '("pline") coords '("c")))
(setq currobj (ssadd (entlast) currobj))
(setq coords (list 
(list 4480.5625 -26.9263) 
(list 4554.585 -26.6763) 
(list 4554.585 -26.4993) 
(list 4480.5625 -26.8493)))
(apply 'command (append '("pline") coords '("c")))
(setq currobj (ssadd (entlast) currobj))
(setq coords (list 
(list 4480.5625 -26.7063) 
(list 4554.585 -26.3563) 
(list 4554.585 -26.1793) 
(list 4480.5625 -26.6293)))
(apply 'command (append '("pline") coords '("c")))
(setq currobj (ssadd (entlast) currobj))
(setq coords (list 
(list 4480.5625 -26.4863) 
(list 4554.585 -26.0363) 
(list 4554.585 -25.8593) 
(list 4480.5625 -26.4093)))
(apply 'command (append '("pline") coords '("c")))
(setq currobj (ssadd (entlast) currobj))
(setq coords (list 
(list 4480.5625 -26.2663) 
(list 4554.585 -25.7163) 
(list 4554.585 -25.5393) 
(list 4480.5625 -26.1893)))
(apply 'command (append '("pline") coords '("c")))
(setq currobj (ssadd (entlast) currobj))
(setq coords (list 
(list 4480.5625 -26.0463) 
(list 4554.585 -25.3963) 
(list 4554.585 -25.2193) 
(list 4480.5625 -25.9693)))
(apply 'command (append '("pline") coords '("c")))
(setq currobj (ssadd (entlast) currobj))
(setq coords (list 
(list 4479.4375 -25.9693) 
(list 4405.415 -25.2193) 
(list 4405.415 -25.3963) 
(list 4479.4375 -26.0463)))
(apply 'command (append '("pline") coords '("c")))
(setq currobj (ssadd (entlast) currobj))
(setq coords (list 
(list 4479.4375 -26.1893) 
(list 4405.415 -25.5393) 
(list 4405.415 -25.7163) 
(list 4479.4375 -26.2663)))
(apply 'command (append '("pline") coords '("c")))
(setq currobj (ssadd (entlast) currobj))
(setq coords (list 
(list 4479.4375 -26.4093) 
(list 4405.415 -25.8593) 
(list 4405.415 -26.0363) 
(list 4479.4375 -26.4863)))
(apply 'command (append '("pline") coords '("c")))
(setq currobj (ssadd (entlast) currobj))
(setq coords (list 
(list 4479.4375 -26.6293) 
(list 4405.415 -26.1793) 
(list 4405.415 -26.3563) 
(list 4479.4375 -26.7063)))
(apply 'command (append '("pline") coords '("c")))
(setq currobj (ssadd (entlast) currobj))
(setq coords (list 
(list 4479.4375 -26.8493) 
(list 4405.415 -26.4993) 
(list 4405.415 -26.6763) 
(list 4479.4375 -26.9263)))
(apply 'command (append '("pline") coords '("c")))
(setq currobj (ssadd (entlast) currobj))
(setq coords (list 
(list 4479.4375 -27.0693) 
(list 4405.415 -26.8193) 
(list 4405.415 -26.9963) 
(list 4479.4375 -27.1463)))
(apply 'command (append '("pline") coords '("c")))
(setq currobj (ssadd (entlast) currobj))
(setq coords (list 
(list 4479.4375 -27.2893) 
(list 4405.415 -27.1393) 
(list 4405.415 -27.3163) 
(list 4479.4375 -27.3663)))
(apply 'command (append '("pline") coords '("c")))
(setq currobj (ssadd (entlast) currobj))
(setq coords (list 
(list 4479.4375 -27.5093) 
(list 4405.415 -27.4593) 
(list 4405.415 -27.6363) 
(list 4479.4375 -27.5863)))
(apply 'command (append '("pline") coords '("c")))
(setq currobj (ssadd (entlast) currobj))
(setq coords (list 
(list 4479.4375 -27.7293) 
(list 4405.415 -27.7793) 
(list 4405.415 -27.9563) 
(list 4479.4375 -27.8063)))
(apply 'command (append '("pline") coords '("c")))
(setq currobj (ssadd (entlast) currobj))
(setq coords (list 
(list 4479.4375 -27.9493) 
(list 4405.415 -28.0993) 
(list 4405.415 -28.2763) 
(list 4479.4375 -28.0263)))
(apply 'command (append '("pline") coords '("c")))
(setq currobj (ssadd (entlast) currobj))
(setq coords (list 
(list 4479.4375 -28.1693) 
(list 4405.415 -28.4193) 
(list 4405.415 -28.5963) 
(list 4479.4375 -28.2463)))
(apply 'command (append '("pline") coords '("c")))
(setq currobj (ssadd (entlast) currobj))
(setq coords (list 
(list 4479.4375 -28.3893) 
(list 4405.415 -28.7393) 
(list 4405.415 -28.9163) 
(list 4479.4375 -28.4663)))
(apply 'command (append '("pline") coords '("c")))
(setq currobj (ssadd (entlast) currobj))
(setq coords (list 
(list 4479.4375 -28.6093) 
(list 4405.415 -29.0593) 
(list 4405.415 -29.2363) 
(list 4479.4375 -28.6863)))
(apply 'command (append '("pline") coords '("c")))
(setq currobj (ssadd (entlast) currobj))
(setq coords (list 
(list 4479.4375 -28.8293) 
(list 4405.415 -29.3793) 
(list 4405.415 -29.5563) 
(list 4479.4375 -28.9063)))
(apply 'command (append '("pline") coords '("c")))
(setq currobj (ssadd (entlast) currobj))
(setq coords (list 
(list 4479.4375 -29.0493) 
(list 4405.415 -29.6993) 
(list 4405.415 -29.8763) 
(list 4479.4375 -29.1263)))
(apply 'command (append '("pline") coords '("c")))
(setq currobj (ssadd (entlast) currobj))
(command "_layer" "set" "nitride" "")
(command "_layer" "set" "text" "")
(command "_circle" "4479.0625,-40.2693" "0.075")
(command "_circle" "4479.0625,-39.9693" "0.075")
(command "_circle" "4479.0625,-39.6693" "0.075")
(command "_circle" "4479.0625,-39.3693" "0.075")
(command "_circle" "4479.0625,-39.0693" "0.075")
(command "_circle" "4478.7625,-40.2693" "0.075")
(command "_circle" "4478.7625,-39.9693" "0.075")
(command "_circle" "4478.7625,-39.6693" "0.075")
(command "_circle" "4478.7625,-39.3693" "0.075")
(command "_circle" "4478.7625,-39.0693" "0.075")
(command "_circle" "4478.4625,-40.2693" "0.075")
(command "_circle" "4478.4625,-39.9693" "0.075")
(command "_circle" "4478.4625,-39.6693" "0.075")
(command "_circle" "4478.4625,-39.3693" "0.075")
(command "_circle" "4478.4625,-39.0693" "0.075")
(command "_circle" "4478.1625,-40.2693" "0.075")
(command "_circle" "4478.1625,-39.9693" "0.075")
(command "_circle" "4478.1625,-39.6693" "0.075")
(command "_circle" "4478.1625,-39.3693" "0.075")
(command "_circle" "4478.1625,-39.0693" "0.075")
(command "_circle" "4477.8625,-40.2693" "0.075")
(command "_circle" "4477.8625,-39.9693" "0.075")
(command "_circle" "4477.8625,-39.6693" "0.075")
(command "_circle" "4477.8625,-39.3693" "0.075")
(command "_circle" "4477.8625,-39.0693" "0.075")
(command "_layer" "set" "nitride" "")
(setq coords (list 
(list 4480.2625 -14.8263) 
(list 4480.2625 100.8184) 
(list 4479.7375 100.8184) 
(list 4479.7375 -14.8263)))
(apply 'command (append '("pline") coords '("c")))
(setq currobj (ssadd (entlast) currobj))
(command "_layer" "set" "prebias" "")
(command "_rectangle" "4479.7375,-14.8263" "4480.2625,100.8184")
(setq currobj (ssadd (entlast) currobj))
(command "_layer" "set" "nitride" "")
(setq coords (list 
(list 4480.2625 100.8184) 
(list 4480.5625 110.8184) 
(list 4480.5625 110.8184) 
(list 4480.5625 111.8184) 
(list 4554.585 111.0684) 
(list 4554.585 116.0114) 
(list 4480.5625 115.2614) 
(list 4480.5625 116.2614) 
(list 4480.5625 116.2614) 
(list 4480.2625 126.2614) 
(list 4479.7375 126.2614) 
(list 4479.4375 116.2614) 
(list 4479.4375 116.2614) 
(list 4479.4375 115.2614) 
(list 4405.415 116.0114) 
(list 4405.415 111.0684) 
(list 4479.4375 111.8184) 
(list 4479.4375 110.8184) 
(list 4479.4375 110.8184) 
(list 4479.7375 100.8184)))
(apply 'command (append '("pline") coords '("c")))
(setq currobj (ssadd (entlast) currobj))
(command "_layer" "set" "prebias" "")
(setq coords (list 
(list 4479.4375 100.8184) 
(list 4479.4375 111.8184) 
(list 4405.415 111.0684) 
(list 4405.415 116.0114) 
(list 4479.4375 115.2614) 
(list 4479.4375 126.2614) 
(list 4480.5625 126.2614) 
(list 4480.5625 115.2614) 
(list 4554.585 116.0114) 
(list 4554.585 111.0684) 
(list 4480.5625 111.8184) 
(list 4480.5625 100.8184)))
(apply 'command (append '("pline") coords '("c")))
(setq currobj (ssadd (entlast) currobj))
(command "_layer" "set" "nitride" "")
(command "_layer" "set" "fda1" "")
(setq coords (list 
(list 4480.5625 111.9614) 
(list 4554.585 111.2114) 
(list 4554.585 111.3884) 
(list 4480.5625 112.0384)))
(apply 'command (append '("pline") coords '("c")))
(setq currobj (ssadd (entlast) currobj))
(setq coords (list 
(list 4480.5625 112.1814) 
(list 4554.585 111.5314) 
(list 4554.585 111.7084) 
(list 4480.5625 112.2584)))
(apply 'command (append '("pline") coords '("c")))
(setq currobj (ssadd (entlast) currobj))
(setq coords (list 
(list 4480.5625 112.4014) 
(list 4554.585 111.8514) 
(list 4554.585 112.0284) 
(list 4480.5625 112.4784)))
(apply 'command (append '("pline") coords '("c")))
(setq currobj (ssadd (entlast) currobj))
(setq coords (list 
(list 4480.5625 112.6214) 
(list 4554.585 112.1714) 
(list 4554.585 112.3484) 
(list 4480.5625 112.6984)))
(apply 'command (append '("pline") coords '("c")))
(setq currobj (ssadd (entlast) currobj))
(setq coords (list 
(list 4480.5625 112.8414) 
(list 4554.585 112.4914) 
(list 4554.585 112.6684) 
(list 4480.5625 112.9184)))
(apply 'command (append '("pline") coords '("c")))
(setq currobj (ssadd (entlast) currobj))
(setq coords (list 
(list 4480.5625 113.0614) 
(list 4554.585 112.8114) 
(list 4554.585 112.9884) 
(list 4480.5625 113.1384)))
(apply 'command (append '("pline") coords '("c")))
(setq currobj (ssadd (entlast) currobj))
(setq coords (list 
(list 4480.5625 113.2814) 
(list 4554.585 113.1314) 
(list 4554.585 113.3084) 
(list 4480.5625 113.3584)))
(apply 'command (append '("pline") coords '("c")))
(setq currobj (ssadd (entlast) currobj))
(setq coords (list 
(list 4480.5625 113.5014) 
(list 4554.585 113.4514) 
(list 4554.585 113.6284) 
(list 4480.5625 113.5784)))
(apply 'command (append '("pline") coords '("c")))
(setq currobj (ssadd (entlast) currobj))
(setq coords (list 
(list 4480.5625 113.7214) 
(list 4554.585 113.7714) 
(list 4554.585 113.9484) 
(list 4480.5625 113.7984)))
(apply 'command (append '("pline") coords '("c")))
(setq currobj (ssadd (entlast) currobj))
(setq coords (list 
(list 4480.5625 113.9414) 
(list 4554.585 114.0914) 
(list 4554.585 114.2684) 
(list 4480.5625 114.0184)))
(apply 'command (append '("pline") coords '("c")))
(setq currobj (ssadd (entlast) currobj))
(setq coords (list 
(list 4480.5625 114.1614) 
(list 4554.585 114.4114) 
(list 4554.585 114.5884) 
(list 4480.5625 114.2384)))
(apply 'command (append '("pline") coords '("c")))
(setq currobj (ssadd (entlast) currobj))
(setq coords (list 
(list 4480.5625 114.3814) 
(list 4554.585 114.7314) 
(list 4554.585 114.9084) 
(list 4480.5625 114.4584)))
(apply 'command (append '("pline") coords '("c")))
(setq currobj (ssadd (entlast) currobj))
(setq coords (list 
(list 4480.5625 114.6014) 
(list 4554.585 115.0514) 
(list 4554.585 115.2284) 
(list 4480.5625 114.6784)))
(apply 'command (append '("pline") coords '("c")))
(setq currobj (ssadd (entlast) currobj))
(setq coords (list 
(list 4480.5625 114.8214) 
(list 4554.585 115.3714) 
(list 4554.585 115.5484) 
(list 4480.5625 114.8984)))
(apply 'command (append '("pline") coords '("c")))
(setq currobj (ssadd (entlast) currobj))
(setq coords (list 
(list 4480.5625 115.0414) 
(list 4554.585 115.6914) 
(list 4554.585 115.8684) 
(list 4480.5625 115.1184)))
(apply 'command (append '("pline") coords '("c")))
(setq currobj (ssadd (entlast) currobj))
(setq coords (list 
(list 4479.4375 115.1184) 
(list 4405.415 115.8684) 
(list 4405.415 115.6914) 
(list 4479.4375 115.0414)))
(apply 'command (append '("pline") coords '("c")))
(setq currobj (ssadd (entlast) currobj))
(setq coords (list 
(list 4479.4375 114.8984) 
(list 4405.415 115.5484) 
(list 4405.415 115.3714) 
(list 4479.4375 114.8214)))
(apply 'command (append '("pline") coords '("c")))
(setq currobj (ssadd (entlast) currobj))
(setq coords (list 
(list 4479.4375 114.6784) 
(list 4405.415 115.2284) 
(list 4405.415 115.0514) 
(list 4479.4375 114.6014)))
(apply 'command (append '("pline") coords '("c")))
(setq currobj (ssadd (entlast) currobj))
(setq coords (list 
(list 4479.4375 114.4584) 
(list 4405.415 114.9084) 
(list 4405.415 114.7314) 
(list 4479.4375 114.3814)))
(apply 'command (append '("pline") coords '("c")))
(setq currobj (ssadd (entlast) currobj))
(setq coords (list 
(list 4479.4375 114.2384) 
(list 4405.415 114.5884) 
(list 4405.415 114.4114) 
(list 4479.4375 114.1614)))
(apply 'command (append '("pline") coords '("c")))
(setq currobj (ssadd (entlast) currobj))
(setq coords (list 
(list 4479.4375 114.0184) 
(list 4405.415 114.2684) 
(list 4405.415 114.0914) 
(list 4479.4375 113.9414)))
(apply 'command (append '("pline") coords '("c")))
(setq currobj (ssadd (entlast) currobj))
(setq coords (list 
(list 4479.4375 113.7984) 
(list 4405.415 113.9484) 
(list 4405.415 113.7714) 
(list 4479.4375 113.7214)))
(apply 'command (append '("pline") coords '("c")))
(setq currobj (ssadd (entlast) currobj))
(setq coords (list 
(list 4479.4375 113.5784) 
(list 4405.415 113.6284) 
(list 4405.415 113.4514) 
(list 4479.4375 113.5014)))
(apply 'command (append '("pline") coords '("c")))
(setq currobj (ssadd (entlast) currobj))
(setq coords (list 
(list 4479.4375 113.3584) 
(list 4405.415 113.3084) 
(list 4405.415 113.1314) 
(list 4479.4375 113.2814)))
(apply 'command (append '("pline") coords '("c")))
(setq currobj (ssadd (entlast) currobj))
(setq coords (list 
(list 4479.4375 113.1384) 
(list 4405.415 112.9884) 
(list 4405.415 112.8114) 
(list 4479.4375 113.0614)))
(apply 'command (append '("pline") coords '("c")))
(setq currobj (ssadd (entlast) currobj))
(setq coords (list 
(list 4479.4375 112.9184) 
(list 4405.415 112.6684) 
(list 4405.415 112.4914) 
(list 4479.4375 112.8414)))
(apply 'command (append '("pline") coords '("c")))
(setq currobj (ssadd (entlast) currobj))
(setq coords (list 
(list 4479.4375 112.6984) 
(list 4405.415 112.3484) 
(list 4405.415 112.1714) 
(list 4479.4375 112.6214)))
(apply 'command (append '("pline") coords '("c")))
(setq currobj (ssadd (entlast) currobj))
(setq coords (list 
(list 4479.4375 112.4784) 
(list 4405.415 112.0284) 
(list 4405.415 111.8514) 
(list 4479.4375 112.4014)))
(apply 'command (append '("pline") coords '("c")))
(setq currobj (ssadd (entlast) currobj))
(setq coords (list 
(list 4479.4375 112.2584) 
(list 4405.415 111.7084) 
(list 4405.415 111.5314) 
(list 4479.4375 112.1814)))
(apply 'command (append '("pline") coords '("c")))
(setq currobj (ssadd (entlast) currobj))
(setq coords (list 
(list 4479.4375 112.0384) 
(list 4405.415 111.3884) 
(list 4405.415 111.2114) 
(list 4479.4375 111.9614)))
(apply 'command (append '("pline") coords '("c")))
(setq currobj (ssadd (entlast) currobj))
(command "_layer" "set" "nitride" "")
(command "_layer" "set" "text" "")
(command "_circle" "4479.0625,100.8184" "0.075")
(command "_circle" "4479.0625,101.1184" "0.075")
(command "_circle" "4479.0625,101.4184" "0.075")
(command "_circle" "4479.0625,101.7184" "0.075")
(command "_circle" "4479.0625,102.0184" "0.075")
(command "_circle" "4478.7625,100.8184" "0.075")
(command "_circle" "4478.7625,101.1184" "0.075")
(command "_circle" "4478.7625,101.4184" "0.075")
(command "_circle" "4478.7625,101.7184" "0.075")
(command "_circle" "4478.7625,102.0184" "0.075")
(command "_circle" "4478.4625,100.8184" "0.075")
(command "_circle" "4478.4625,101.1184" "0.075")
(command "_circle" "4478.4625,101.4184" "0.075")
(command "_circle" "4478.4625,101.7184" "0.075")
(command "_circle" "4478.4625,102.0184" "0.075")
(command "_circle" "4478.1625,100.8184" "0.075")
(command "_circle" "4478.1625,101.1184" "0.075")
(command "_circle" "4478.1625,101.4184" "0.075")
(command "_circle" "4478.1625,101.7184" "0.075")
(command "_circle" "4478.1625,102.0184" "0.075")
(command "_circle" "4477.8625,100.8184" "0.075")
(command "_circle" "4477.8625,101.1184" "0.075")
(command "_circle" "4477.8625,101.4184" "0.075")
(command "_circle" "4477.8625,101.7184" "0.075")
(command "_circle" "4477.8625,102.0184" "0.075")
(command "_layer" "set" "nitride" "")
(setq coords (list 
(list 4480.2625 126.2614) 
(list 4480.2625 241.9061) 
(list 4479.7375 241.9061) 
(list 4479.7375 126.2614)))
(apply 'command (append '("pline") coords '("c")))
(setq currobj (ssadd (entlast) currobj))
(command "_layer" "set" "prebias" "")
(command "_rectangle" "4479.7375,126.2614" "4480.2625,241.9061")
(setq currobj (ssadd (entlast) currobj))
(command "_layer" "set" "nitride" "")
(setq coords (list 
(list 4480.2625 241.9061) 
(list 4480.5625 251.9061) 
(list 4480.5625 251.9061) 
(list 4480.5625 252.9061) 
(list 4554.585 252.1561) 
(list 4554.585 257.0991) 
(list 4480.5625 256.3491) 
(list 4480.5625 257.3491) 
(list 4480.5625 257.3491) 
(list 4480.2625 267.3491) 
(list 4479.7375 267.3491) 
(list 4479.4375 257.3491) 
(list 4479.4375 257.3491) 
(list 4479.4375 256.3491) 
(list 4405.415 257.0991) 
(list 4405.415 252.1561) 
(list 4479.4375 252.9061) 
(list 4479.4375 251.9061) 
(list 4479.4375 251.9061) 
(list 4479.7375 241.9061)))
(apply 'command (append '("pline") coords '("c")))
(setq currobj (ssadd (entlast) currobj))
(command "_layer" "set" "prebias" "")
(setq coords (list 
(list 4479.4375 241.9061) 
(list 4479.4375 252.9061) 
(list 4405.415 252.1561) 
(list 4405.415 257.0991) 
(list 4479.4375 256.3491) 
(list 4479.4375 267.3491) 
(list 4480.5625 267.3491) 
(list 4480.5625 256.3491) 
(list 4554.585 257.0991) 
(list 4554.585 252.1561) 
(list 4480.5625 252.9061) 
(list 4480.5625 241.9061)))
(apply 'command (append '("pline") coords '("c")))
(setq currobj (ssadd (entlast) currobj))
(command "_layer" "set" "nitride" "")
(command "_layer" "set" "fda1" "")
(setq coords (list 
(list 4480.5625 253.0491) 
(list 4554.585 252.2991) 
(list 4554.585 252.4761) 
(list 4480.5625 253.1261)))
(apply 'command (append '("pline") coords '("c")))
(setq currobj (ssadd (entlast) currobj))
(setq coords (list 
(list 4480.5625 253.2691) 
(list 4554.585 252.6191) 
(list 4554.585 252.7961) 
(list 4480.5625 253.3461)))
(apply 'command (append '("pline") coords '("c")))
(setq currobj (ssadd (entlast) currobj))
(setq coords (list 
(list 4480.5625 253.4891) 
(list 4554.585 252.9391) 
(list 4554.585 253.1161) 
(list 4480.5625 253.5661)))
(apply 'command (append '("pline") coords '("c")))
(setq currobj (ssadd (entlast) currobj))
(setq coords (list 
(list 4480.5625 253.7091) 
(list 4554.585 253.2591) 
(list 4554.585 253.4361) 
(list 4480.5625 253.7861)))
(apply 'command (append '("pline") coords '("c")))
(setq currobj (ssadd (entlast) currobj))
(setq coords (list 
(list 4480.5625 253.9291) 
(list 4554.585 253.5791) 
(list 4554.585 253.7561) 
(list 4480.5625 254.0061)))
(apply 'command (append '("pline") coords '("c")))
(setq currobj (ssadd (entlast) currobj))
(setq coords (list 
(list 4480.5625 254.1491) 
(list 4554.585 253.8991) 
(list 4554.585 254.0761) 
(list 4480.5625 254.2261)))
(apply 'command (append '("pline") coords '("c")))
(setq currobj (ssadd (entlast) currobj))
(setq coords (list 
(list 4480.5625 254.3691) 
(list 4554.585 254.2191) 
(list 4554.585 254.3961) 
(list 4480.5625 254.4461)))
(apply 'command (append '("pline") coords '("c")))
(setq currobj (ssadd (entlast) currobj))
(setq coords (list 
(list 4480.5625 254.5891) 
(list 4554.585 254.5391) 
(list 4554.585 254.7161) 
(list 4480.5625 254.6661)))
(apply 'command (append '("pline") coords '("c")))
(setq currobj (ssadd (entlast) currobj))
(setq coords (list 
(list 4480.5625 254.8091) 
(list 4554.585 254.8591) 
(list 4554.585 255.0361) 
(list 4480.5625 254.8861)))
(apply 'command (append '("pline") coords '("c")))
(setq currobj (ssadd (entlast) currobj))
(setq coords (list 
(list 4480.5625 255.0291) 
(list 4554.585 255.1791) 
(list 4554.585 255.3561) 
(list 4480.5625 255.1061)))
(apply 'command (append '("pline") coords '("c")))
(setq currobj (ssadd (entlast) currobj))
(setq coords (list 
(list 4480.5625 255.2491) 
(list 4554.585 255.4991) 
(list 4554.585 255.6761) 
(list 4480.5625 255.3261)))
(apply 'command (append '("pline") coords '("c")))
(setq currobj (ssadd (entlast) currobj))
(setq coords (list 
(list 4480.5625 255.4691) 
(list 4554.585 255.8191) 
(list 4554.585 255.9961) 
(list 4480.5625 255.5461)))
(apply 'command (append '("pline") coords '("c")))
(setq currobj (ssadd (entlast) currobj))
(setq coords (list 
(list 4480.5625 255.6891) 
(list 4554.585 256.1391) 
(list 4554.585 256.3161) 
(list 4480.5625 255.7661)))
(apply 'command (append '("pline") coords '("c")))
(setq currobj (ssadd (entlast) currobj))
(setq coords (list 
(list 4480.5625 255.9091) 
(list 4554.585 256.4591) 
(list 4554.585 256.6361) 
(list 4480.5625 255.9861)))
(apply 'command (append '("pline") coords '("c")))
(setq currobj (ssadd (entlast) currobj))
(setq coords (list 
(list 4480.5625 256.1291) 
(list 4554.585 256.7791) 
(list 4554.585 256.9561) 
(list 4480.5625 256.2061)))
(apply 'command (append '("pline") coords '("c")))
(setq currobj (ssadd (entlast) currobj))
(setq coords (list 
(list 4479.4375 256.2061) 
(list 4405.415 256.9561) 
(list 4405.415 256.7791) 
(list 4479.4375 256.1291)))
(apply 'command (append '("pline") coords '("c")))
(setq currobj (ssadd (entlast) currobj))
(setq coords (list 
(list 4479.4375 255.9861) 
(list 4405.415 256.6361) 
(list 4405.415 256.4591) 
(list 4479.4375 255.9091)))
(apply 'command (append '("pline") coords '("c")))
(setq currobj (ssadd (entlast) currobj))
(setq coords (list 
(list 4479.4375 255.7661) 
(list 4405.415 256.3161) 
(list 4405.415 256.1391) 
(list 4479.4375 255.6891)))
(apply 'command (append '("pline") coords '("c")))
(setq currobj (ssadd (entlast) currobj))
(setq coords (list 
(list 4479.4375 255.5461) 
(list 4405.415 255.9961) 
(list 4405.415 255.8191) 
(list 4479.4375 255.4691)))
(apply 'command (append '("pline") coords '("c")))
(setq currobj (ssadd (entlast) currobj))
(setq coords (list 
(list 4479.4375 255.3261) 
(list 4405.415 255.6761) 
(list 4405.415 255.4991) 
(list 4479.4375 255.2491)))
(apply 'command (append '("pline") coords '("c")))
(setq currobj (ssadd (entlast) currobj))
(setq coords (list 
(list 4479.4375 255.1061) 
(list 4405.415 255.3561) 
(list 4405.415 255.1791) 
(list 4479.4375 255.0291)))
(apply 'command (append '("pline") coords '("c")))
(setq currobj (ssadd (entlast) currobj))
(setq coords (list 
(list 4479.4375 254.8861) 
(list 4405.415 255.0361) 
(list 4405.415 254.8591) 
(list 4479.4375 254.8091)))
(apply 'command (append '("pline") coords '("c")))
(setq currobj (ssadd (entlast) currobj))
(setq coords (list 
(list 4479.4375 254.6661) 
(list 4405.415 254.7161) 
(list 4405.415 254.5391) 
(list 4479.4375 254.5891)))
(apply 'command (append '("pline") coords '("c")))
(setq currobj (ssadd (entlast) currobj))
(setq coords (list 
(list 4479.4375 254.4461) 
(list 4405.415 254.3961) 
(list 4405.415 254.2191) 
(list 4479.4375 254.3691)))
(apply 'command (append '("pline") coords '("c")))
(setq currobj (ssadd (entlast) currobj))
(setq coords (list 
(list 4479.4375 254.2261) 
(list 4405.415 254.0761) 
(list 4405.415 253.8991) 
(list 4479.4375 254.1491)))
(apply 'command (append '("pline") coords '("c")))
(setq currobj (ssadd (entlast) currobj))
(setq coords (list 
(list 4479.4375 254.0061) 
(list 4405.415 253.7561) 
(list 4405.415 253.5791) 
(list 4479.4375 253.9291)))
(apply 'command (append '("pline") coords '("c")))
(setq currobj (ssadd (entlast) currobj))
(setq coords (list 
(list 4479.4375 253.7861) 
(list 4405.415 253.4361) 
(list 4405.415 253.2591) 
(list 4479.4375 253.7091)))
(apply 'command (append '("pline") coords '("c")))
(setq currobj (ssadd (entlast) currobj))
(setq coords (list 
(list 4479.4375 253.5661) 
(list 4405.415 253.1161) 
(list 4405.415 252.9391) 
(list 4479.4375 253.4891)))
(apply 'command (append '("pline") coords '("c")))
(setq currobj (ssadd (entlast) currobj))
(setq coords (list 
(list 4479.4375 253.3461) 
(list 4405.415 252.7961) 
(list 4405.415 252.6191) 
(list 4479.4375 253.2691)))
(apply 'command (append '("pline") coords '("c")))
(setq currobj (ssadd (entlast) currobj))
(setq coords (list 
(list 4479.4375 253.1261) 
(list 4405.415 252.4761) 
(list 4405.415 252.2991) 
(list 4479.4375 253.0491)))
(apply 'command (append '("pline") coords '("c")))
(setq currobj (ssadd (entlast) currobj))
(command "_layer" "set" "nitride" "")
(command "_layer" "set" "text" "")
(command "_circle" "4479.0625,241.9061" "0.075")
(command "_circle" "4479.0625,242.2061" "0.075")
(command "_circle" "4479.0625,242.5061" "0.075")
(command "_circle" "4479.0625,242.8061" "0.075")
(command "_circle" "4479.0625,243.1061" "0.075")
(command "_circle" "4478.7625,241.9061" "0.075")
(command "_circle" "4478.7625,242.2061" "0.075")
(command "_circle" "4478.7625,242.5061" "0.075")
(command "_circle" "4478.7625,242.8061" "0.075")
(command "_circle" "4478.7625,243.1061" "0.075")
(command "_circle" "4478.4625,241.9061" "0.075")
(command "_circle" "4478.4625,242.2061" "0.075")
(command "_circle" "4478.4625,242.5061" "0.075")
(command "_circle" "4478.4625,242.8061" "0.075")
(command "_circle" "4478.4625,243.1061" "0.075")
(command "_circle" "4478.1625,241.9061" "0.075")
(command "_circle" "4478.1625,242.2061" "0.075")
(command "_circle" "4478.1625,242.5061" "0.075")
(command "_circle" "4478.1625,242.8061" "0.075")
(command "_circle" "4478.1625,243.1061" "0.075")
(command "_circle" "4477.8625,241.9061" "0.075")
(command "_circle" "4477.8625,242.2061" "0.075")
(command "_circle" "4477.8625,242.5061" "0.075")
(command "_circle" "4477.8625,242.8061" "0.075")
(command "_circle" "4477.8625,243.1061" "0.075")
(command "_layer" "set" "nitride" "")
(setq coords (list 
(list 4480.2625 267.3491) 
(list 4480.2625 382.9939) 
(list 4479.7375 382.9939) 
(list 4479.7375 267.3491)))
(apply 'command (append '("pline") coords '("c")))
(setq currobj (ssadd (entlast) currobj))
(command "_layer" "set" "prebias" "")
(command "_rectangle" "4479.7375,267.3491" "4480.2625,382.9939")
(setq currobj (ssadd (entlast) currobj))
(command "_layer" "set" "nitride" "")
(setq coords (list 
(list 4480.2625 382.9939) 
(list 4480.5625 392.9939) 
(list 4480.5625 392.9939) 
(list 4480.5625 393.9939) 
(list 4554.585 393.2439) 
(list 4554.585 398.1869) 
(list 4480.5625 397.4369) 
(list 4480.5625 398.4369) 
(list 4480.5625 398.4369) 
(list 4480.2625 408.4369) 
(list 4479.7375 408.4369) 
(list 4479.4375 398.4369) 
(list 4479.4375 398.4369) 
(list 4479.4375 397.4369) 
(list 4405.415 398.1869) 
(list 4405.415 393.2439) 
(list 4479.4375 393.9939) 
(list 4479.4375 392.9939) 
(list 4479.4375 392.9939) 
(list 4479.7375 382.9939)))
(apply 'command (append '("pline") coords '("c")))
(setq currobj (ssadd (entlast) currobj))
(command "_layer" "set" "prebias" "")
(setq coords (list 
(list 4479.4375 382.9939) 
(list 4479.4375 393.9939) 
(list 4405.415 393.2439) 
(list 4405.415 398.1869) 
(list 4479.4375 397.4369) 
(list 4479.4375 408.4369) 
(list 4480.5625 408.4369) 
(list 4480.5625 397.4369) 
(list 4554.585 398.1869) 
(list 4554.585 393.2439) 
(list 4480.5625 393.9939) 
(list 4480.5625 382.9939)))
(apply 'command (append '("pline") coords '("c")))
(setq currobj (ssadd (entlast) currobj))
(command "_layer" "set" "nitride" "")
(command "_layer" "set" "fda1" "")
(setq coords (list 
(list 4480.5625 394.1369) 
(list 4554.585 393.3869) 
(list 4554.585 393.5639) 
(list 4480.5625 394.2139)))
(apply 'command (append '("pline") coords '("c")))
(setq currobj (ssadd (entlast) currobj))
(setq coords (list 
(list 4480.5625 394.3569) 
(list 4554.585 393.7069) 
(list 4554.585 393.8839) 
(list 4480.5625 394.4339)))
(apply 'command (append '("pline") coords '("c")))
(setq currobj (ssadd (entlast) currobj))
(setq coords (list 
(list 4480.5625 394.5769) 
(list 4554.585 394.0269) 
(list 4554.585 394.2039) 
(list 4480.5625 394.6539)))
(apply 'command (append '("pline") coords '("c")))
(setq currobj (ssadd (entlast) currobj))
(setq coords (list 
(list 4480.5625 394.7969) 
(list 4554.585 394.3469) 
(list 4554.585 394.5239) 
(list 4480.5625 394.8739)))
(apply 'command (append '("pline") coords '("c")))
(setq currobj (ssadd (entlast) currobj))
(setq coords (list 
(list 4480.5625 395.0169) 
(list 4554.585 394.6669) 
(list 4554.585 394.8439) 
(list 4480.5625 395.0939)))
(apply 'command (append '("pline") coords '("c")))
(setq currobj (ssadd (entlast) currobj))
(setq coords (list 
(list 4480.5625 395.2369) 
(list 4554.585 394.9869) 
(list 4554.585 395.1639) 
(list 4480.5625 395.3139)))
(apply 'command (append '("pline") coords '("c")))
(setq currobj (ssadd (entlast) currobj))
(setq coords (list 
(list 4480.5625 395.4569) 
(list 4554.585 395.3069) 
(list 4554.585 395.4839) 
(list 4480.5625 395.5339)))
(apply 'command (append '("pline") coords '("c")))
(setq currobj (ssadd (entlast) currobj))
(setq coords (list 
(list 4480.5625 395.6769) 
(list 4554.585 395.6269) 
(list 4554.585 395.8039) 
(list 4480.5625 395.7539)))
(apply 'command (append '("pline") coords '("c")))
(setq currobj (ssadd (entlast) currobj))
(setq coords (list 
(list 4480.5625 395.8969) 
(list 4554.585 395.9469) 
(list 4554.585 396.1239) 
(list 4480.5625 395.9739)))
(apply 'command (append '("pline") coords '("c")))
(setq currobj (ssadd (entlast) currobj))
(setq coords (list 
(list 4480.5625 396.1169) 
(list 4554.585 396.2669) 
(list 4554.585 396.4439) 
(list 4480.5625 396.1939)))
(apply 'command (append '("pline") coords '("c")))
(setq currobj (ssadd (entlast) currobj))
(setq coords (list 
(list 4480.5625 396.3369) 
(list 4554.585 396.5869) 
(list 4554.585 396.7639) 
(list 4480.5625 396.4139)))
(apply 'command (append '("pline") coords '("c")))
(setq currobj (ssadd (entlast) currobj))
(setq coords (list 
(list 4480.5625 396.5569) 
(list 4554.585 396.9069) 
(list 4554.585 397.0839) 
(list 4480.5625 396.6339)))
(apply 'command (append '("pline") coords '("c")))
(setq currobj (ssadd (entlast) currobj))
(setq coords (list 
(list 4480.5625 396.7769) 
(list 4554.585 397.2269) 
(list 4554.585 397.4039) 
(list 4480.5625 396.8539)))
(apply 'command (append '("pline") coords '("c")))
(setq currobj (ssadd (entlast) currobj))
(setq coords (list 
(list 4480.5625 396.9969) 
(list 4554.585 397.5469) 
(list 4554.585 397.7239) 
(list 4480.5625 397.0739)))
(apply 'command (append '("pline") coords '("c")))
(setq currobj (ssadd (entlast) currobj))
(setq coords (list 
(list 4480.5625 397.2169) 
(list 4554.585 397.8669) 
(list 4554.585 398.0439) 
(list 4480.5625 397.2939)))
(apply 'command (append '("pline") coords '("c")))
(setq currobj (ssadd (entlast) currobj))
(setq coords (list 
(list 4479.4375 397.2939) 
(list 4405.415 398.0439) 
(list 4405.415 397.8669) 
(list 4479.4375 397.2169)))
(apply 'command (append '("pline") coords '("c")))
(setq currobj (ssadd (entlast) currobj))
(setq coords (list 
(list 4479.4375 397.0739) 
(list 4405.415 397.7239) 
(list 4405.415 397.5469) 
(list 4479.4375 396.9969)))
(apply 'command (append '("pline") coords '("c")))
(setq currobj (ssadd (entlast) currobj))
(setq coords (list 
(list 4479.4375 396.8539) 
(list 4405.415 397.4039) 
(list 4405.415 397.2269) 
(list 4479.4375 396.7769)))
(apply 'command (append '("pline") coords '("c")))
(setq currobj (ssadd (entlast) currobj))
(setq coords (list 
(list 4479.4375 396.6339) 
(list 4405.415 397.0839) 
(list 4405.415 396.9069) 
(list 4479.4375 396.5569)))
(apply 'command (append '("pline") coords '("c")))
(setq currobj (ssadd (entlast) currobj))
(setq coords (list 
(list 4479.4375 396.4139) 
(list 4405.415 396.7639) 
(list 4405.415 396.5869) 
(list 4479.4375 396.3369)))
(apply 'command (append '("pline") coords '("c")))
(setq currobj (ssadd (entlast) currobj))
(setq coords (list 
(list 4479.4375 396.1939) 
(list 4405.415 396.4439) 
(list 4405.415 396.2669) 
(list 4479.4375 396.1169)))
(apply 'command (append '("pline") coords '("c")))
(setq currobj (ssadd (entlast) currobj))
(setq coords (list 
(list 4479.4375 395.9739) 
(list 4405.415 396.1239) 
(list 4405.415 395.9469) 
(list 4479.4375 395.8969)))
(apply 'command (append '("pline") coords '("c")))
(setq currobj (ssadd (entlast) currobj))
(setq coords (list 
(list 4479.4375 395.7539) 
(list 4405.415 395.8039) 
(list 4405.415 395.6269) 
(list 4479.4375 395.6769)))
(apply 'command (append '("pline") coords '("c")))
(setq currobj (ssadd (entlast) currobj))
(setq coords (list 
(list 4479.4375 395.5339) 
(list 4405.415 395.4839) 
(list 4405.415 395.3069) 
(list 4479.4375 395.4569)))
(apply 'command (append '("pline") coords '("c")))
(setq currobj (ssadd (entlast) currobj))
(setq coords (list 
(list 4479.4375 395.3139) 
(list 4405.415 395.1639) 
(list 4405.415 394.9869) 
(list 4479.4375 395.2369)))
(apply 'command (append '("pline") coords '("c")))
(setq currobj (ssadd (entlast) currobj))
(setq coords (list 
(list 4479.4375 395.0939) 
(list 4405.415 394.8439) 
(list 4405.415 394.6669) 
(list 4479.4375 395.0169)))
(apply 'command (append '("pline") coords '("c")))
(setq currobj (ssadd (entlast) currobj))
(setq coords (list 
(list 4479.4375 394.8739) 
(list 4405.415 394.5239) 
(list 4405.415 394.3469) 
(list 4479.4375 394.7969)))
(apply 'command (append '("pline") coords '("c")))
(setq currobj (ssadd (entlast) currobj))
(setq coords (list 
(list 4479.4375 394.6539) 
(list 4405.415 394.2039) 
(list 4405.415 394.0269) 
(list 4479.4375 394.5769)))
(apply 'command (append '("pline") coords '("c")))
(setq currobj (ssadd (entlast) currobj))
(setq coords (list 
(list 4479.4375 394.4339) 
(list 4405.415 393.8839) 
(list 4405.415 393.7069) 
(list 4479.4375 394.3569)))
(apply 'command (append '("pline") coords '("c")))
(setq currobj (ssadd (entlast) currobj))
(setq coords (list 
(list 4479.4375 394.2139) 
(list 4405.415 393.5639) 
(list 4405.415 393.3869) 
(list 4479.4375 394.1369)))
(apply 'command (append '("pline") coords '("c")))
(setq currobj (ssadd (entlast) currobj))
(command "_layer" "set" "nitride" "")
(command "_layer" "set" "text" "")
(command "_circle" "4479.0625,382.9939" "0.075")
(command "_circle" "4479.0625,383.2939" "0.075")
(command "_circle" "4479.0625,383.5939" "0.075")
(command "_circle" "4479.0625,383.8939" "0.075")
(command "_circle" "4479.0625,384.1939" "0.075")
(command "_circle" "4478.7625,382.9939" "0.075")
(command "_circle" "4478.7625,383.2939" "0.075")
(command "_circle" "4478.7625,383.5939" "0.075")
(command "_circle" "4478.7625,383.8939" "0.075")
(command "_circle" "4478.7625,384.1939" "0.075")
(command "_circle" "4478.4625,382.9939" "0.075")
(command "_circle" "4478.4625,383.2939" "0.075")
(command "_circle" "4478.4625,383.5939" "0.075")
(command "_circle" "4478.4625,383.8939" "0.075")
(command "_circle" "4478.4625,384.1939" "0.075")
(command "_circle" "4478.1625,382.9939" "0.075")
(command "_circle" "4478.1625,383.2939" "0.075")
(command "_circle" "4478.1625,383.5939" "0.075")
(command "_circle" "4478.1625,383.8939" "0.075")
(command "_circle" "4478.1625,384.1939" "0.075")
(command "_circle" "4477.8625,382.9939" "0.075")
(command "_circle" "4477.8625,383.2939" "0.075")
(command "_circle" "4477.8625,383.5939" "0.075")
(command "_circle" "4477.8625,383.8939" "0.075")
(command "_circle" "4477.8625,384.1939" "0.075")
(command "_layer" "set" "nitride" "")
(setq coords (list 
(list 4480.2625 408.4369) 
(list 4480.2625 524.0816) 
(list 4479.7375 524.0816) 
(list 4479.7375 408.4369)))
(apply 'command (append '("pline") coords '("c")))
(setq currobj (ssadd (entlast) currobj))
(command "_layer" "set" "prebias" "")
(command "_rectangle" "4479.7375,408.4369" "4480.2625,524.0816")
(setq currobj (ssadd (entlast) currobj))
(command "_layer" "set" "nitride" "")
(setq coords (list 
(list 4480.2625 524.0816) 
(list 4480.5625 534.0816) 
(list 4480.5625 534.0816) 
(list 4480.5625 535.0816) 
(list 4554.585 534.3316) 
(list 4554.585 539.2746) 
(list 4480.5625 538.5246) 
(list 4480.5625 539.5246) 
(list 4480.5625 539.5246) 
(list 4480.2625 549.5246) 
(list 4479.7375 549.5246) 
(list 4479.4375 539.5246) 
(list 4479.4375 539.5246) 
(list 4479.4375 538.5246) 
(list 4405.415 539.2746) 
(list 4405.415 534.3316) 
(list 4479.4375 535.0816) 
(list 4479.4375 534.0816) 
(list 4479.4375 534.0816) 
(list 4479.7375 524.0816)))
(apply 'command (append '("pline") coords '("c")))
(setq currobj (ssadd (entlast) currobj))
(command "_layer" "set" "prebias" "")
(setq coords (list 
(list 4479.4375 524.0816) 
(list 4479.4375 535.0816) 
(list 4405.415 534.3316) 
(list 4405.415 539.2746) 
(list 4479.4375 538.5246) 
(list 4479.4375 549.5246) 
(list 4480.5625 549.5246) 
(list 4480.5625 538.5246) 
(list 4554.585 539.2746) 
(list 4554.585 534.3316) 
(list 4480.5625 535.0816) 
(list 4480.5625 524.0816)))
(apply 'command (append '("pline") coords '("c")))
(setq currobj (ssadd (entlast) currobj))
(command "_layer" "set" "nitride" "")
(command "_layer" "set" "fda1" "")
(setq coords (list 
(list 4480.5625 535.2246) 
(list 4554.585 534.4746) 
(list 4554.585 534.6516) 
(list 4480.5625 535.3016)))
(apply 'command (append '("pline") coords '("c")))
(setq currobj (ssadd (entlast) currobj))
(setq coords (list 
(list 4480.5625 535.4446) 
(list 4554.585 534.7946) 
(list 4554.585 534.9716) 
(list 4480.5625 535.5216)))
(apply 'command (append '("pline") coords '("c")))
(setq currobj (ssadd (entlast) currobj))
(setq coords (list 
(list 4480.5625 535.6646) 
(list 4554.585 535.1146) 
(list 4554.585 535.2916) 
(list 4480.5625 535.7416)))
(apply 'command (append '("pline") coords '("c")))
(setq currobj (ssadd (entlast) currobj))
(setq coords (list 
(list 4480.5625 535.8846) 
(list 4554.585 535.4346) 
(list 4554.585 535.6116) 
(list 4480.5625 535.9616)))
(apply 'command (append '("pline") coords '("c")))
(setq currobj (ssadd (entlast) currobj))
(setq coords (list 
(list 4480.5625 536.1046) 
(list 4554.585 535.7546) 
(list 4554.585 535.9316) 
(list 4480.5625 536.1816)))
(apply 'command (append '("pline") coords '("c")))
(setq currobj (ssadd (entlast) currobj))
(setq coords (list 
(list 4480.5625 536.3246) 
(list 4554.585 536.0746) 
(list 4554.585 536.2516) 
(list 4480.5625 536.4016)))
(apply 'command (append '("pline") coords '("c")))
(setq currobj (ssadd (entlast) currobj))
(setq coords (list 
(list 4480.5625 536.5446) 
(list 4554.585 536.3946) 
(list 4554.585 536.5716) 
(list 4480.5625 536.6216)))
(apply 'command (append '("pline") coords '("c")))
(setq currobj (ssadd (entlast) currobj))
(setq coords (list 
(list 4480.5625 536.7646) 
(list 4554.585 536.7146) 
(list 4554.585 536.8916) 
(list 4480.5625 536.8416)))
(apply 'command (append '("pline") coords '("c")))
(setq currobj (ssadd (entlast) currobj))
(setq coords (list 
(list 4480.5625 536.9846) 
(list 4554.585 537.0346) 
(list 4554.585 537.2116) 
(list 4480.5625 537.0616)))
(apply 'command (append '("pline") coords '("c")))
(setq currobj (ssadd (entlast) currobj))
(setq coords (list 
(list 4480.5625 537.2046) 
(list 4554.585 537.3546) 
(list 4554.585 537.5316) 
(list 4480.5625 537.2816)))
(apply 'command (append '("pline") coords '("c")))
(setq currobj (ssadd (entlast) currobj))
(setq coords (list 
(list 4480.5625 537.4246) 
(list 4554.585 537.6746) 
(list 4554.585 537.8516) 
(list 4480.5625 537.5016)))
(apply 'command (append '("pline") coords '("c")))
(setq currobj (ssadd (entlast) currobj))
(setq coords (list 
(list 4480.5625 537.6446) 
(list 4554.585 537.9946) 
(list 4554.585 538.1716) 
(list 4480.5625 537.7216)))
(apply 'command (append '("pline") coords '("c")))
(setq currobj (ssadd (entlast) currobj))
(setq coords (list 
(list 4480.5625 537.8646) 
(list 4554.585 538.3146) 
(list 4554.585 538.4916) 
(list 4480.5625 537.9416)))
(apply 'command (append '("pline") coords '("c")))
(setq currobj (ssadd (entlast) currobj))
(setq coords (list 
(list 4480.5625 538.0846) 
(list 4554.585 538.6346) 
(list 4554.585 538.8116) 
(list 4480.5625 538.1616)))
(apply 'command (append '("pline") coords '("c")))
(setq currobj (ssadd (entlast) currobj))
(setq coords (list 
(list 4480.5625 538.3046) 
(list 4554.585 538.9546) 
(list 4554.585 539.1316) 
(list 4480.5625 538.3816)))
(apply 'command (append '("pline") coords '("c")))
(setq currobj (ssadd (entlast) currobj))
(setq coords (list 
(list 4479.4375 538.3816) 
(list 4405.415 539.1316) 
(list 4405.415 538.9546) 
(list 4479.4375 538.3046)))
(apply 'command (append '("pline") coords '("c")))
(setq currobj (ssadd (entlast) currobj))
(setq coords (list 
(list 4479.4375 538.1616) 
(list 4405.415 538.8116) 
(list 4405.415 538.6346) 
(list 4479.4375 538.0846)))
(apply 'command (append '("pline") coords '("c")))
(setq currobj (ssadd (entlast) currobj))
(setq coords (list 
(list 4479.4375 537.9416) 
(list 4405.415 538.4916) 
(list 4405.415 538.3146) 
(list 4479.4375 537.8646)))
(apply 'command (append '("pline") coords '("c")))
(setq currobj (ssadd (entlast) currobj))
(setq coords (list 
(list 4479.4375 537.7216) 
(list 4405.415 538.1716) 
(list 4405.415 537.9946) 
(list 4479.4375 537.6446)))
(apply 'command (append '("pline") coords '("c")))
(setq currobj (ssadd (entlast) currobj))
(setq coords (list 
(list 4479.4375 537.5016) 
(list 4405.415 537.8516) 
(list 4405.415 537.6746) 
(list 4479.4375 537.4246)))
(apply 'command (append '("pline") coords '("c")))
(setq currobj (ssadd (entlast) currobj))
(setq coords (list 
(list 4479.4375 537.2816) 
(list 4405.415 537.5316) 
(list 4405.415 537.3546) 
(list 4479.4375 537.2046)))
(apply 'command (append '("pline") coords '("c")))
(setq currobj (ssadd (entlast) currobj))
(setq coords (list 
(list 4479.4375 537.0616) 
(list 4405.415 537.2116) 
(list 4405.415 537.0346) 
(list 4479.4375 536.9846)))
(apply 'command (append '("pline") coords '("c")))
(setq currobj (ssadd (entlast) currobj))
(setq coords (list 
(list 4479.4375 536.8416) 
(list 4405.415 536.8916) 
(list 4405.415 536.7146) 
(list 4479.4375 536.7646)))
(apply 'command (append '("pline") coords '("c")))
(setq currobj (ssadd (entlast) currobj))
(setq coords (list 
(list 4479.4375 536.6216) 
(list 4405.415 536.5716) 
(list 4405.415 536.3946) 
(list 4479.4375 536.5446)))
(apply 'command (append '("pline") coords '("c")))
(setq currobj (ssadd (entlast) currobj))
(setq coords (list 
(list 4479.4375 536.4016) 
(list 4405.415 536.2516) 
(list 4405.415 536.0746) 
(list 4479.4375 536.3246)))
(apply 'command (append '("pline") coords '("c")))
(setq currobj (ssadd (entlast) currobj))
(setq coords (list 
(list 4479.4375 536.1816) 
(list 4405.415 535.9316) 
(list 4405.415 535.7546) 
(list 4479.4375 536.1046)))
(apply 'command (append '("pline") coords '("c")))
(setq currobj (ssadd (entlast) currobj))
(setq coords (list 
(list 4479.4375 535.9616) 
(list 4405.415 535.6116) 
(list 4405.415 535.4346) 
(list 4479.4375 535.8846)))
(apply 'command (append '("pline") coords '("c")))
(setq currobj (ssadd (entlast) currobj))
(setq coords (list 
(list 4479.4375 535.7416) 
(list 4405.415 535.2916) 
(list 4405.415 535.1146) 
(list 4479.4375 535.6646)))
(apply 'command (append '("pline") coords '("c")))
(setq currobj (ssadd (entlast) currobj))
(setq coords (list 
(list 4479.4375 535.5216) 
(list 4405.415 534.9716) 
(list 4405.415 534.7946) 
(list 4479.4375 535.4446)))
(apply 'command (append '("pline") coords '("c")))
(setq currobj (ssadd (entlast) currobj))
(setq coords (list 
(list 4479.4375 535.3016) 
(list 4405.415 534.6516) 
(list 4405.415 534.4746) 
(list 4479.4375 535.2246)))
(apply 'command (append '("pline") coords '("c")))
(setq currobj (ssadd (entlast) currobj))
(command "_layer" "set" "nitride" "")
(command "_layer" "set" "text" "")
(command "_circle" "4479.0625,524.0816" "0.075")
(command "_circle" "4479.0625,524.3816" "0.075")
(command "_circle" "4479.0625,524.6816" "0.075")
(command "_circle" "4479.0625,524.9816" "0.075")
(command "_circle" "4479.0625,525.2816" "0.075")
(command "_circle" "4478.7625,524.0816" "0.075")
(command "_circle" "4478.7625,524.3816" "0.075")
(command "_circle" "4478.7625,524.6816" "0.075")
(command "_circle" "4478.7625,524.9816" "0.075")
(command "_circle" "4478.7625,525.2816" "0.075")
(command "_circle" "4478.4625,524.0816" "0.075")
(command "_circle" "4478.4625,524.3816" "0.075")
(command "_circle" "4478.4625,524.6816" "0.075")
(command "_circle" "4478.4625,524.9816" "0.075")
(command "_circle" "4478.4625,525.2816" "0.075")
(command "_circle" "4478.1625,524.0816" "0.075")
(command "_circle" "4478.1625,524.3816" "0.075")
(command "_circle" "4478.1625,524.6816" "0.075")
(command "_circle" "4478.1625,524.9816" "0.075")
(command "_circle" "4478.1625,525.2816" "0.075")
(command "_circle" "4477.8625,524.0816" "0.075")
(command "_circle" "4477.8625,524.3816" "0.075")
(command "_circle" "4477.8625,524.6816" "0.075")
(command "_circle" "4477.8625,524.9816" "0.075")
(command "_circle" "4477.8625,525.2816" "0.075")
(command "_layer" "set" "nitride" "")
(setq coords (list 
(list 4480.2625 549.5246) 
(list 4480.2625 665.1693) 
(list 4479.7375 665.1693) 
(list 4479.7375 549.5246)))
(apply 'command (append '("pline") coords '("c")))
(setq currobj (ssadd (entlast) currobj))
(command "_layer" "set" "prebias" "")
(command "_rectangle" "4479.7375,549.5246" "4480.2625,665.1693")
(setq currobj (ssadd (entlast) currobj))
(command "_layer" "set" "nitride" "")
(setq coords (list 
(list 4480.2625 665.1693) 
(list 4480.5625 675.1693) 
(list 4480.5625 675.1693) 
(list 4480.5625 676.1693) 
(list 4554.585 675.4193) 
(list 4554.585 680.3623) 
(list 4480.5625 679.6123) 
(list 4480.5625 680.6123) 
(list 4480.5625 680.6123) 
(list 4480.2625 690.6123) 
(list 4479.7375 690.6123) 
(list 4479.4375 680.6123) 
(list 4479.4375 680.6123) 
(list 4479.4375 679.6123) 
(list 4405.415 680.3623) 
(list 4405.415 675.4193) 
(list 4479.4375 676.1693) 
(list 4479.4375 675.1693) 
(list 4479.4375 675.1693) 
(list 4479.7375 665.1693)))
(apply 'command (append '("pline") coords '("c")))
(setq currobj (ssadd (entlast) currobj))
(command "_layer" "set" "prebias" "")
(setq coords (list 
(list 4479.4375 665.1693) 
(list 4479.4375 676.1693) 
(list 4405.415 675.4193) 
(list 4405.415 680.3623) 
(list 4479.4375 679.6123) 
(list 4479.4375 690.6123) 
(list 4480.5625 690.6123) 
(list 4480.5625 679.6123) 
(list 4554.585 680.3623) 
(list 4554.585 675.4193) 
(list 4480.5625 676.1693) 
(list 4480.5625 665.1693)))
(apply 'command (append '("pline") coords '("c")))
(setq currobj (ssadd (entlast) currobj))
(command "_layer" "set" "nitride" "")
(command "_layer" "set" "fda1" "")
(setq coords (list 
(list 4480.5625 676.3123) 
(list 4554.585 675.5623) 
(list 4554.585 675.7393) 
(list 4480.5625 676.3893)))
(apply 'command (append '("pline") coords '("c")))
(setq currobj (ssadd (entlast) currobj))
(setq coords (list 
(list 4480.5625 676.5323) 
(list 4554.585 675.8823) 
(list 4554.585 676.0593) 
(list 4480.5625 676.6093)))
(apply 'command (append '("pline") coords '("c")))
(setq currobj (ssadd (entlast) currobj))
(setq coords (list 
(list 4480.5625 676.7523) 
(list 4554.585 676.2023) 
(list 4554.585 676.3793) 
(list 4480.5625 676.8293)))
(apply 'command (append '("pline") coords '("c")))
(setq currobj (ssadd (entlast) currobj))
(setq coords (list 
(list 4480.5625 676.9723) 
(list 4554.585 676.5223) 
(list 4554.585 676.6993) 
(list 4480.5625 677.0493)))
(apply 'command (append '("pline") coords '("c")))
(setq currobj (ssadd (entlast) currobj))
(setq coords (list 
(list 4480.5625 677.1923) 
(list 4554.585 676.8423) 
(list 4554.585 677.0193) 
(list 4480.5625 677.2693)))
(apply 'command (append '("pline") coords '("c")))
(setq currobj (ssadd (entlast) currobj))
(setq coords (list 
(list 4480.5625 677.4123) 
(list 4554.585 677.1623) 
(list 4554.585 677.3393) 
(list 4480.5625 677.4893)))
(apply 'command (append '("pline") coords '("c")))
(setq currobj (ssadd (entlast) currobj))
(setq coords (list 
(list 4480.5625 677.6323) 
(list 4554.585 677.4823) 
(list 4554.585 677.6593) 
(list 4480.5625 677.7093)))
(apply 'command (append '("pline") coords '("c")))
(setq currobj (ssadd (entlast) currobj))
(setq coords (list 
(list 4480.5625 677.8523) 
(list 4554.585 677.8023) 
(list 4554.585 677.9793) 
(list 4480.5625 677.9293)))
(apply 'command (append '("pline") coords '("c")))
(setq currobj (ssadd (entlast) currobj))
(setq coords (list 
(list 4480.5625 678.0723) 
(list 4554.585 678.1223) 
(list 4554.585 678.2993) 
(list 4480.5625 678.1493)))
(apply 'command (append '("pline") coords '("c")))
(setq currobj (ssadd (entlast) currobj))
(setq coords (list 
(list 4480.5625 678.2923) 
(list 4554.585 678.4423) 
(list 4554.585 678.6193) 
(list 4480.5625 678.3693)))
(apply 'command (append '("pline") coords '("c")))
(setq currobj (ssadd (entlast) currobj))
(setq coords (list 
(list 4480.5625 678.5123) 
(list 4554.585 678.7623) 
(list 4554.585 678.9393) 
(list 4480.5625 678.5893)))
(apply 'command (append '("pline") coords '("c")))
(setq currobj (ssadd (entlast) currobj))
(setq coords (list 
(list 4480.5625 678.7323) 
(list 4554.585 679.0823) 
(list 4554.585 679.2593) 
(list 4480.5625 678.8093)))
(apply 'command (append '("pline") coords '("c")))
(setq currobj (ssadd (entlast) currobj))
(setq coords (list 
(list 4480.5625 678.9523) 
(list 4554.585 679.4023) 
(list 4554.585 679.5793) 
(list 4480.5625 679.0293)))
(apply 'command (append '("pline") coords '("c")))
(setq currobj (ssadd (entlast) currobj))
(setq coords (list 
(list 4480.5625 679.1723) 
(list 4554.585 679.7223) 
(list 4554.585 679.8993) 
(list 4480.5625 679.2493)))
(apply 'command (append '("pline") coords '("c")))
(setq currobj (ssadd (entlast) currobj))
(setq coords (list 
(list 4480.5625 679.3923) 
(list 4554.585 680.0423) 
(list 4554.585 680.2193) 
(list 4480.5625 679.4693)))
(apply 'command (append '("pline") coords '("c")))
(setq currobj (ssadd (entlast) currobj))
(setq coords (list 
(list 4479.4375 679.4693) 
(list 4405.415 680.2193) 
(list 4405.415 680.0423) 
(list 4479.4375 679.3923)))
(apply 'command (append '("pline") coords '("c")))
(setq currobj (ssadd (entlast) currobj))
(setq coords (list 
(list 4479.4375 679.2493) 
(list 4405.415 679.8993) 
(list 4405.415 679.7223) 
(list 4479.4375 679.1723)))
(apply 'command (append '("pline") coords '("c")))
(setq currobj (ssadd (entlast) currobj))
(setq coords (list 
(list 4479.4375 679.0293) 
(list 4405.415 679.5793) 
(list 4405.415 679.4023) 
(list 4479.4375 678.9523)))
(apply 'command (append '("pline") coords '("c")))
(setq currobj (ssadd (entlast) currobj))
(setq coords (list 
(list 4479.4375 678.8093) 
(list 4405.415 679.2593) 
(list 4405.415 679.0823) 
(list 4479.4375 678.7323)))
(apply 'command (append '("pline") coords '("c")))
(setq currobj (ssadd (entlast) currobj))
(setq coords (list 
(list 4479.4375 678.5893) 
(list 4405.415 678.9393) 
(list 4405.415 678.7623) 
(list 4479.4375 678.5123)))
(apply 'command (append '("pline") coords '("c")))
(setq currobj (ssadd (entlast) currobj))
(setq coords (list 
(list 4479.4375 678.3693) 
(list 4405.415 678.6193) 
(list 4405.415 678.4423) 
(list 4479.4375 678.2923)))
(apply 'command (append '("pline") coords '("c")))
(setq currobj (ssadd (entlast) currobj))
(setq coords (list 
(list 4479.4375 678.1493) 
(list 4405.415 678.2993) 
(list 4405.415 678.1223) 
(list 4479.4375 678.0723)))
(apply 'command (append '("pline") coords '("c")))
(setq currobj (ssadd (entlast) currobj))
(setq coords (list 
(list 4479.4375 677.9293) 
(list 4405.415 677.9793) 
(list 4405.415 677.8023) 
(list 4479.4375 677.8523)))
(apply 'command (append '("pline") coords '("c")))
(setq currobj (ssadd (entlast) currobj))
(setq coords (list 
(list 4479.4375 677.7093) 
(list 4405.415 677.6593) 
(list 4405.415 677.4823) 
(list 4479.4375 677.6323)))
(apply 'command (append '("pline") coords '("c")))
(setq currobj (ssadd (entlast) currobj))
(setq coords (list 
(list 4479.4375 677.4893) 
(list 4405.415 677.3393) 
(list 4405.415 677.1623) 
(list 4479.4375 677.4123)))
(apply 'command (append '("pline") coords '("c")))
(setq currobj (ssadd (entlast) currobj))
(setq coords (list 
(list 4479.4375 677.2693) 
(list 4405.415 677.0193) 
(list 4405.415 676.8423) 
(list 4479.4375 677.1923)))
(apply 'command (append '("pline") coords '("c")))
(setq currobj (ssadd (entlast) currobj))
(setq coords (list 
(list 4479.4375 677.0493) 
(list 4405.415 676.6993) 
(list 4405.415 676.5223) 
(list 4479.4375 676.9723)))
(apply 'command (append '("pline") coords '("c")))
(setq currobj (ssadd (entlast) currobj))
(setq coords (list 
(list 4479.4375 676.8293) 
(list 4405.415 676.3793) 
(list 4405.415 676.2023) 
(list 4479.4375 676.7523)))
(apply 'command (append '("pline") coords '("c")))
(setq currobj (ssadd (entlast) currobj))
(setq coords (list 
(list 4479.4375 676.6093) 
(list 4405.415 676.0593) 
(list 4405.415 675.8823) 
(list 4479.4375 676.5323)))
(apply 'command (append '("pline") coords '("c")))
(setq currobj (ssadd (entlast) currobj))
(setq coords (list 
(list 4479.4375 676.3893) 
(list 4405.415 675.7393) 
(list 4405.415 675.5623) 
(list 4479.4375 676.3123)))
(apply 'command (append '("pline") coords '("c")))
(setq currobj (ssadd (entlast) currobj))
(command "_layer" "set" "nitride" "")
(command "_layer" "set" "text" "")
(command "_circle" "4479.0625,665.1693" "0.075")
(command "_circle" "4479.0625,665.4693" "0.075")
(command "_circle" "4479.0625,665.7693" "0.075")
(command "_circle" "4479.0625,666.0693" "0.075")
(command "_circle" "4479.0625,666.3693" "0.075")
(command "_circle" "4478.7625,665.1693" "0.075")
(command "_circle" "4478.7625,665.4693" "0.075")
(command "_circle" "4478.7625,665.7693" "0.075")
(command "_circle" "4478.7625,666.0693" "0.075")
(command "_circle" "4478.7625,666.3693" "0.075")
(command "_circle" "4478.4625,665.1693" "0.075")
(command "_circle" "4478.4625,665.4693" "0.075")
(command "_circle" "4478.4625,665.7693" "0.075")
(command "_circle" "4478.4625,666.0693" "0.075")
(command "_circle" "4478.4625,666.3693" "0.075")
(command "_circle" "4478.1625,665.1693" "0.075")
(command "_circle" "4478.1625,665.4693" "0.075")
(command "_circle" "4478.1625,665.7693" "0.075")
(command "_circle" "4478.1625,666.0693" "0.075")
(command "_circle" "4478.1625,666.3693" "0.075")
(command "_circle" "4477.8625,665.1693" "0.075")
(command "_circle" "4477.8625,665.4693" "0.075")
(command "_circle" "4477.8625,665.7693" "0.075")
(command "_circle" "4477.8625,666.0693" "0.075")
(command "_circle" "4477.8625,666.3693" "0.075")
(command "_layer" "set" "nitride" "")
(setq coords (list 
(list 4480.2625 690.6123) 
(list 4480.2625 806.257) 
(list 4479.7375 806.257) 
(list 4479.7375 690.6123)))
(apply 'command (append '("pline") coords '("c")))
(setq currobj (ssadd (entlast) currobj))
(command "_layer" "set" "prebias" "")
(command "_rectangle" "4479.7375,690.6123" "4480.2625,806.257")
(setq currobj (ssadd (entlast) currobj))
(command "_layer" "set" "nitride" "")
(setq coords (list 
(list 4480.2625 806.257) 
(list 4480.5625 816.257) 
(list 4480.5625 816.257) 
(list 4480.5625 817.257) 
(list 4554.585 816.507) 
(list 4554.585 821.45) 
(list 4480.5625 820.7) 
(list 4480.5625 821.7) 
(list 4480.5625 821.7) 
(list 4480.2625 831.7) 
(list 4479.7375 831.7) 
(list 4479.4375 821.7) 
(list 4479.4375 821.7) 
(list 4479.4375 820.7) 
(list 4405.415 821.45) 
(list 4405.415 816.507) 
(list 4479.4375 817.257) 
(list 4479.4375 816.257) 
(list 4479.4375 816.257) 
(list 4479.7375 806.257)))
(apply 'command (append '("pline") coords '("c")))
(setq currobj (ssadd (entlast) currobj))
(command "_layer" "set" "prebias" "")
(setq coords (list 
(list 4479.4375 806.257) 
(list 4479.4375 817.257) 
(list 4405.415 816.507) 
(list 4405.415 821.45) 
(list 4479.4375 820.7) 
(list 4479.4375 831.7) 
(list 4480.5625 831.7) 
(list 4480.5625 820.7) 
(list 4554.585 821.45) 
(list 4554.585 816.507) 
(list 4480.5625 817.257) 
(list 4480.5625 806.257)))
(apply 'command (append '("pline") coords '("c")))
(setq currobj (ssadd (entlast) currobj))
(command "_layer" "set" "nitride" "")
(command "_layer" "set" "fda1" "")
(setq coords (list 
(list 4480.5625 817.4) 
(list 4554.585 816.65) 
(list 4554.585 816.827) 
(list 4480.5625 817.477)))
(apply 'command (append '("pline") coords '("c")))
(setq currobj (ssadd (entlast) currobj))
(setq coords (list 
(list 4480.5625 817.62) 
(list 4554.585 816.97) 
(list 4554.585 817.147) 
(list 4480.5625 817.697)))
(apply 'command (append '("pline") coords '("c")))
(setq currobj (ssadd (entlast) currobj))
(setq coords (list 
(list 4480.5625 817.84) 
(list 4554.585 817.29) 
(list 4554.585 817.467) 
(list 4480.5625 817.917)))
(apply 'command (append '("pline") coords '("c")))
(setq currobj (ssadd (entlast) currobj))
(setq coords (list 
(list 4480.5625 818.06) 
(list 4554.585 817.61) 
(list 4554.585 817.787) 
(list 4480.5625 818.137)))
(apply 'command (append '("pline") coords '("c")))
(setq currobj (ssadd (entlast) currobj))
(setq coords (list 
(list 4480.5625 818.28) 
(list 4554.585 817.93) 
(list 4554.585 818.107) 
(list 4480.5625 818.357)))
(apply 'command (append '("pline") coords '("c")))
(setq currobj (ssadd (entlast) currobj))
(setq coords (list 
(list 4480.5625 818.5) 
(list 4554.585 818.25) 
(list 4554.585 818.427) 
(list 4480.5625 818.577)))
(apply 'command (append '("pline") coords '("c")))
(setq currobj (ssadd (entlast) currobj))
(setq coords (list 
(list 4480.5625 818.72) 
(list 4554.585 818.57) 
(list 4554.585 818.747) 
(list 4480.5625 818.797)))
(apply 'command (append '("pline") coords '("c")))
(setq currobj (ssadd (entlast) currobj))
(setq coords (list 
(list 4480.5625 818.94) 
(list 4554.585 818.89) 
(list 4554.585 819.067) 
(list 4480.5625 819.017)))
(apply 'command (append '("pline") coords '("c")))
(setq currobj (ssadd (entlast) currobj))
(setq coords (list 
(list 4480.5625 819.16) 
(list 4554.585 819.21) 
(list 4554.585 819.387) 
(list 4480.5625 819.237)))
(apply 'command (append '("pline") coords '("c")))
(setq currobj (ssadd (entlast) currobj))
(setq coords (list 
(list 4480.5625 819.38) 
(list 4554.585 819.53) 
(list 4554.585 819.707) 
(list 4480.5625 819.457)))
(apply 'command (append '("pline") coords '("c")))
(setq currobj (ssadd (entlast) currobj))
(setq coords (list 
(list 4480.5625 819.6) 
(list 4554.585 819.85) 
(list 4554.585 820.027) 
(list 4480.5625 819.677)))
(apply 'command (append '("pline") coords '("c")))
(setq currobj (ssadd (entlast) currobj))
(setq coords (list 
(list 4480.5625 819.82) 
(list 4554.585 820.17) 
(list 4554.585 820.347) 
(list 4480.5625 819.897)))
(apply 'command (append '("pline") coords '("c")))
(setq currobj (ssadd (entlast) currobj))
(setq coords (list 
(list 4480.5625 820.04) 
(list 4554.585 820.49) 
(list 4554.585 820.667) 
(list 4480.5625 820.117)))
(apply 'command (append '("pline") coords '("c")))
(setq currobj (ssadd (entlast) currobj))
(setq coords (list 
(list 4480.5625 820.26) 
(list 4554.585 820.81) 
(list 4554.585 820.987) 
(list 4480.5625 820.337)))
(apply 'command (append '("pline") coords '("c")))
(setq currobj (ssadd (entlast) currobj))
(setq coords (list 
(list 4480.5625 820.48) 
(list 4554.585 821.13) 
(list 4554.585 821.307) 
(list 4480.5625 820.557)))
(apply 'command (append '("pline") coords '("c")))
(setq currobj (ssadd (entlast) currobj))
(setq coords (list 
(list 4479.4375 820.557) 
(list 4405.415 821.307) 
(list 4405.415 821.13) 
(list 4479.4375 820.48)))
(apply 'command (append '("pline") coords '("c")))
(setq currobj (ssadd (entlast) currobj))
(setq coords (list 
(list 4479.4375 820.337) 
(list 4405.415 820.987) 
(list 4405.415 820.81) 
(list 4479.4375 820.26)))
(apply 'command (append '("pline") coords '("c")))
(setq currobj (ssadd (entlast) currobj))
(setq coords (list 
(list 4479.4375 820.117) 
(list 4405.415 820.667) 
(list 4405.415 820.49) 
(list 4479.4375 820.04)))
(apply 'command (append '("pline") coords '("c")))
(setq currobj (ssadd (entlast) currobj))
(setq coords (list 
(list 4479.4375 819.897) 
(list 4405.415 820.347) 
(list 4405.415 820.17) 
(list 4479.4375 819.82)))
(apply 'command (append '("pline") coords '("c")))
(setq currobj (ssadd (entlast) currobj))
(setq coords (list 
(list 4479.4375 819.677) 
(list 4405.415 820.027) 
(list 4405.415 819.85) 
(list 4479.4375 819.6)))
(apply 'command (append '("pline") coords '("c")))
(setq currobj (ssadd (entlast) currobj))
(setq coords (list 
(list 4479.4375 819.457) 
(list 4405.415 819.707) 
(list 4405.415 819.53) 
(list 4479.4375 819.38)))
(apply 'command (append '("pline") coords '("c")))
(setq currobj (ssadd (entlast) currobj))
(setq coords (list 
(list 4479.4375 819.237) 
(list 4405.415 819.387) 
(list 4405.415 819.21) 
(list 4479.4375 819.16)))
(apply 'command (append '("pline") coords '("c")))
(setq currobj (ssadd (entlast) currobj))
(setq coords (list 
(list 4479.4375 819.017) 
(list 4405.415 819.067) 
(list 4405.415 818.89) 
(list 4479.4375 818.94)))
(apply 'command (append '("pline") coords '("c")))
(setq currobj (ssadd (entlast) currobj))
(setq coords (list 
(list 4479.4375 818.797) 
(list 4405.415 818.747) 
(list 4405.415 818.57) 
(list 4479.4375 818.72)))
(apply 'command (append '("pline") coords '("c")))
(setq currobj (ssadd (entlast) currobj))
(setq coords (list 
(list 4479.4375 818.577) 
(list 4405.415 818.427) 
(list 4405.415 818.25) 
(list 4479.4375 818.5)))
(apply 'command (append '("pline") coords '("c")))
(setq currobj (ssadd (entlast) currobj))
(setq coords (list 
(list 4479.4375 818.357) 
(list 4405.415 818.107) 
(list 4405.415 817.93) 
(list 4479.4375 818.28)))
(apply 'command (append '("pline") coords '("c")))
(setq currobj (ssadd (entlast) currobj))
(setq coords (list 
(list 4479.4375 818.137) 
(list 4405.415 817.787) 
(list 4405.415 817.61) 
(list 4479.4375 818.06)))
(apply 'command (append '("pline") coords '("c")))
(setq currobj (ssadd (entlast) currobj))
(setq coords (list 
(list 4479.4375 817.917) 
(list 4405.415 817.467) 
(list 4405.415 817.29) 
(list 4479.4375 817.84)))
(apply 'command (append '("pline") coords '("c")))
(setq currobj (ssadd (entlast) currobj))
(setq coords (list 
(list 4479.4375 817.697) 
(list 4405.415 817.147) 
(list 4405.415 816.97) 
(list 4479.4375 817.62)))
(apply 'command (append '("pline") coords '("c")))
(setq currobj (ssadd (entlast) currobj))
(setq coords (list 
(list 4479.4375 817.477) 
(list 4405.415 816.827) 
(list 4405.415 816.65) 
(list 4479.4375 817.4)))
(apply 'command (append '("pline") coords '("c")))
(setq currobj (ssadd (entlast) currobj))
(command "_layer" "set" "nitride" "")
(command "_layer" "set" "text" "")
(command "_circle" "4479.0625,806.257" "0.075")
(command "_circle" "4479.0625,806.557" "0.075")
(command "_circle" "4479.0625,806.857" "0.075")
(command "_circle" "4479.0625,807.157" "0.075")
(command "_circle" "4479.0625,807.457" "0.075")
(command "_circle" "4478.7625,806.257" "0.075")
(command "_circle" "4478.7625,806.557" "0.075")
(command "_circle" "4478.7625,806.857" "0.075")
(command "_circle" "4478.7625,807.157" "0.075")
(command "_circle" "4478.7625,807.457" "0.075")
(command "_circle" "4478.4625,806.257" "0.075")
(command "_circle" "4478.4625,806.557" "0.075")
(command "_circle" "4478.4625,806.857" "0.075")
(command "_circle" "4478.4625,807.157" "0.075")
(command "_circle" "4478.4625,807.457" "0.075")
(command "_circle" "4478.1625,806.257" "0.075")
(command "_circle" "4478.1625,806.557" "0.075")
(command "_circle" "4478.1625,806.857" "0.075")
(command "_circle" "4478.1625,807.157" "0.075")
(command "_circle" "4478.1625,807.457" "0.075")
(command "_circle" "4477.8625,806.257" "0.075")
(command "_circle" "4477.8625,806.557" "0.075")
(command "_circle" "4477.8625,806.857" "0.075")
(command "_circle" "4477.8625,807.157" "0.075")
(command "_circle" "4477.8625,807.457" "0.075")
(command "_layer" "set" "nitride" "")
(setq coords (list 
(list 4480.2625 831.7) 
(list 4480.2625 836.7) 
(list 4479.7375 836.7) 
(list 4479.7375 831.7)))
(apply 'command (append '("pline") coords '("c")))
(setq currobj (ssadd (entlast) currobj))
(command "_layer" "set" "prebias" "")
(command "_rectangle" "4479.7375,831.7" "4480.2625,836.7")
(setq currobj (ssadd (entlast) currobj))
(command "_layer" "set" "nitride" "")
(setq cooledsinglenanobeam14 currobj)
(setq currobj nil)
(setq currobj (ssadd))
; DRAWING PHOTONIC CRYSTAL
(command "_layer" "set" "negYjunc" "")
(setq coords (list 
(list 4480.125 866.7) 
(list 4480 851.7) 
(list 4480 866.7)))
(apply 'command (append '("pline") coords '("c")))
(setq currobj (ssadd (entlast) currobj))
(setq coords (list 
(list 4480.2625 836.7) 
(list 4480.405 866.7) 
(list 4481.122 866.7) 
(list 4481.122 836.7)))
(apply 'command (append '("pline") coords '("c")))
(setq currobj (ssadd (entlast) currobj))
(setq coords (list 
(list 4479.875 866.7) 
(list 4480 851.7) 
(list 4480 866.7)))
(apply 'command (append '("pline") coords '("c")))
(setq currobj (ssadd (entlast) currobj))
(setq coords (list 
(list 4479.7375 836.7) 
(list 4479.595 866.7) 
(list 4478.878 866.7) 
(list 4478.878 836.7)))
(apply 'command (append '("pline") coords '("c")))
(setq currobj (ssadd (entlast) currobj))
(command "_layer" "set" "nitride" "")
(setq yjunction14 currobj)
(setq currobj nil)
(setq currobj (ssadd))
(setq tap14 nil)
(setq tap14 (ssadd))
(command "_layer" "set" "phc" "")
(setq coords (list 
(list 4480 866.7) 
(list 4480.125 866.7) 
(list 4480.125 866.7103) 
(list 4480.125 866.7206) 
(list 4480.125 866.7308) 
(list 4480.125 866.7411) 
(list 4480.125 866.7514) 
(list 4480.125 866.7617) 
(list 4480.125 866.7719) 
(list 4480.125 866.7822) 
(list 4480.125 866.7925) 
(list 4480.125 866.8028) 
(list 4480.125 866.8131) 
(list 4480.125 866.8233) 
(list 4480.125 866.8336) 
(list 4480.125 866.8439) 
(list 4480.125 866.8542) 
(list 4480.125 866.8644) 
(list 4480.125 866.8747) 
(list 4480.125 866.885) 
(list 4480.125 866.8953) 
(list 4480.125 866.9056) 
(list 4480.125 866.9158) 
(list 4480.125 866.9261) 
(list 4480.125 866.9364) 
(list 4480.125 866.9467) 
(list 4480.125 866.9569) 
(list 4480.125 866.9672) 
(list 4480.125 866.9775) 
(list 4480.125 866.9878) 
(list 4480.125 866.9981) 
(list 4480.125 867.0083) 
(list 4480.125 867.0186) 
(list 4480.125 867.0289) 
(list 4480.125 867.0392) 
(list 4480.125 867.0494) 
(list 4480.125 867.0597) 
(list 4480.125 867.07) 
(list 4480 867.07)))
(apply 'command (append '("pline") coords '("c")))
(setq tap14 (ssadd (entlast) tap14))
(command "_mirror" (entlast) "" "4480,900" "4480,901" "No")
(setq tap14 (ssadd (entlast) tap14))
(setq coords (list 
(list 4480.4154 866.7) 
(list 4480.405 866.7) 
(list 4480.4053 866.7103) 
(list 4480.4055 866.7206) 
(list 4480.4058 866.7308) 
(list 4480.4059 866.7411) 
(list 4480.406 866.7514) 
(list 4480.406 866.7617) 
(list 4480.4059 866.7719) 
(list 4480.4057 866.7822) 
(list 4480.4054 866.7925) 
(list 4480.405 866.8028) 
(list 4480.4046 866.8131) 
(list 4480.4041 866.8233) 
(list 4480.4035 866.8336) 
(list 4480.403 866.8439) 
(list 4480.4025 866.8542) 
(list 4480.402 866.8644) 
(list 4480.4017 866.8747) 
(list 4480.4014 866.885) 
(list 4480.4013 866.8953) 
(list 4480.4013 866.9056) 
(list 4480.4015 866.9158) 
(list 4480.4019 866.9261) 
(list 4480.4024 866.9364) 
(list 4480.4031 866.9467) 
(list 4480.404 866.9569) 
(list 4480.4051 866.9672) 
(list 4480.4062 866.9775) 
(list 4480.4074 866.9878) 
(list 4480.4087 866.9981) 
(list 4480.41 867.0083) 
(list 4480.4112 867.0186) 
(list 4480.4124 867.0289) 
(list 4480.4135 867.0392) 
(list 4480.4143 867.0494) 
(list 4480.415 867.0597) 
(list 4480.4154 867.07) 
(list 4480.4154 867.07)))
(apply 'command (append '("pline") coords '("c")))
(setq tap14 (ssadd (entlast) tap14))
(command "_mirror" (entlast) "" "4480,900" "4480,901" "No")
(setq tap14 (ssadd (entlast) tap14))
(setq coords (list 
(list 4481.122 866.7) 
(list 4480.4154 866.7) 
(list 4480.4154 866.7103) 
(list 4480.4154 866.7206) 
(list 4480.4154 866.7308) 
(list 4480.4154 866.7411) 
(list 4480.4154 866.7514) 
(list 4480.4154 866.7617) 
(list 4480.4154 866.7719) 
(list 4480.4154 866.7822) 
(list 4480.4154 866.7925) 
(list 4480.4154 866.8028) 
(list 4480.4154 866.8131) 
(list 4480.4154 866.8233) 
(list 4480.4154 866.8336) 
(list 4480.4154 866.8439) 
(list 4480.4154 866.8542) 
(list 4480.4154 866.8644) 
(list 4480.4154 866.8747) 
(list 4480.4154 866.885) 
(list 4480.4154 866.8953) 
(list 4480.4154 866.9056) 
(list 4480.4154 866.9158) 
(list 4480.4154 866.9261) 
(list 4480.4154 866.9364) 
(list 4480.4154 866.9467) 
(list 4480.4154 866.9569) 
(list 4480.4154 866.9672) 
(list 4480.4154 866.9775) 
(list 4480.4154 866.9878) 
(list 4480.4154 866.9981) 
(list 4480.4154 867.0083) 
(list 4480.4154 867.0186) 
(list 4480.4154 867.0289) 
(list 4480.4154 867.0392) 
(list 4480.4154 867.0494) 
(list 4480.4154 867.0597) 
(list 4480.4154 867.07) 
(list 4481.122 867.07)))
(apply 'command (append '("pline") coords '("c")))
(setq tap14 (ssadd (entlast) tap14))
(command "_mirror" (entlast) "" "4480,900" "4480,901" "No")
(setq tap14 (ssadd (entlast) tap14))
(setq coords (list 
(list 4480 867.07) 
(list 4480.125 867.07) 
(list 4480.125 867.0803) 
(list 4480.125 867.0906) 
(list 4480.125 867.1008) 
(list 4480.125 867.1111) 
(list 4480.125 867.1214) 
(list 4480.125 867.1317) 
(list 4480.125 867.1419) 
(list 4480.125 867.1522) 
(list 4480.125 867.1625) 
(list 4480.125 867.1728) 
(list 4480.125 867.1831) 
(list 4480.125 867.1933) 
(list 4480.125 867.2036) 
(list 4480.125 867.2139) 
(list 4480.125 867.2242) 
(list 4480.125 867.2344) 
(list 4480.125 867.2447) 
(list 4480.125 867.255) 
(list 4480.125 867.2653) 
(list 4480.125 867.2756) 
(list 4480.125 867.2858) 
(list 4480.125 867.2961) 
(list 4480.125 867.3064) 
(list 4480.125 867.3167) 
(list 4480.125 867.3269) 
(list 4480.125 867.3372) 
(list 4480.125 867.3475) 
(list 4480.125 867.3578) 
(list 4480.125 867.3681) 
(list 4480.125 867.3783) 
(list 4480.125 867.3886) 
(list 4480.125 867.3989) 
(list 4480.125 867.4092) 
(list 4480.125 867.4194) 
(list 4480.125 867.4297) 
(list 4480.125 867.44) 
(list 4480 867.44)))
(apply 'command (append '("pline") coords '("c")))
(setq tap14 (ssadd (entlast) tap14))
(command "_mirror" (entlast) "" "4480,900" "4480,901" "No")
(setq tap14 (ssadd (entlast) tap14))
(setq coords (list 
(list 4480.4258 867.07) 
(list 4480.4154 867.07) 
(list 4480.4156 867.0803) 
(list 4480.4154 867.0906) 
(list 4480.415 867.1008) 
(list 4480.4143 867.1111) 
(list 4480.4133 867.1214) 
(list 4480.412 867.1317) 
(list 4480.4105 867.1419) 
(list 4480.4088 867.1522) 
(list 4480.407 867.1625) 
(list 4480.4051 867.1728) 
(list 4480.4032 867.1831) 
(list 4480.4013 867.1933) 
(list 4480.3995 867.2036) 
(list 4480.3979 867.2139) 
(list 4480.3965 867.2242) 
(list 4480.3954 867.2344) 
(list 4480.3946 867.2447) 
(list 4480.3942 867.255) 
(list 4480.3942 867.2653) 
(list 4480.3946 867.2756) 
(list 4480.3955 867.2858) 
(list 4480.3967 867.2961) 
(list 4480.3984 867.3064) 
(list 4480.4003 867.3167) 
(list 4480.4026 867.3269) 
(list 4480.4051 867.3372) 
(list 4480.4078 867.3475) 
(list 4480.4106 867.3578) 
(list 4480.4133 867.3681) 
(list 4480.416 867.3783) 
(list 4480.4185 867.3886) 
(list 4480.4208 867.3989) 
(list 4480.4227 867.4092) 
(list 4480.4242 867.4194) 
(list 4480.4252 867.4297) 
(list 4480.4258 867.44) 
(list 4480.4258 867.44)))
(apply 'command (append '("pline") coords '("c")))
(setq tap14 (ssadd (entlast) tap14))
(command "_mirror" (entlast) "" "4480,900" "4480,901" "No")
(setq tap14 (ssadd (entlast) tap14))
(setq coords (list 
(list 4481.122 867.07) 
(list 4480.4258 867.07) 
(list 4480.4258 867.0803) 
(list 4480.4258 867.0906) 
(list 4480.4258 867.1008) 
(list 4480.4258 867.1111) 
(list 4480.4258 867.1214) 
(list 4480.4258 867.1317) 
(list 4480.4258 867.1419) 
(list 4480.4258 867.1522) 
(list 4480.4258 867.1625) 
(list 4480.4258 867.1728) 
(list 4480.4258 867.1831) 
(list 4480.4258 867.1933) 
(list 4480.4258 867.2036) 
(list 4480.4258 867.2139) 
(list 4480.4258 867.2242) 
(list 4480.4258 867.2344) 
(list 4480.4258 867.2447) 
(list 4480.4258 867.255) 
(list 4480.4258 867.2653) 
(list 4480.4258 867.2756) 
(list 4480.4258 867.2858) 
(list 4480.4258 867.2961) 
(list 4480.4258 867.3064) 
(list 4480.4258 867.3167) 
(list 4480.4258 867.3269) 
(list 4480.4258 867.3372) 
(list 4480.4258 867.3475) 
(list 4480.4258 867.3578) 
(list 4480.4258 867.3681) 
(list 4480.4258 867.3783) 
(list 4480.4258 867.3886) 
(list 4480.4258 867.3989) 
(list 4480.4258 867.4092) 
(list 4480.4258 867.4194) 
(list 4480.4258 867.4297) 
(list 4480.4258 867.44) 
(list 4481.122 867.44)))
(apply 'command (append '("pline") coords '("c")))
(setq tap14 (ssadd (entlast) tap14))
(command "_mirror" (entlast) "" "4480,900" "4480,901" "No")
(setq tap14 (ssadd (entlast) tap14))
(setq coords (list 
(list 4480 867.44) 
(list 4480.125 867.44) 
(list 4480.125 867.4503) 
(list 4480.125 867.4606) 
(list 4480.125 867.4708) 
(list 4480.125 867.4811) 
(list 4480.125 867.4914) 
(list 4480.125 867.5017) 
(list 4480.125 867.5119) 
(list 4480.125 867.5222) 
(list 4480.125 867.5325) 
(list 4480.125 867.5428) 
(list 4480.125 867.5531) 
(list 4480.125 867.5633) 
(list 4480.125 867.5736) 
(list 4480.125 867.5839) 
(list 4480.125 867.5942) 
(list 4480.125 867.6044) 
(list 4480.125 867.6147) 
(list 4480.125 867.625) 
(list 4480.125 867.6353) 
(list 4480.125 867.6456) 
(list 4480.125 867.6558) 
(list 4480.125 867.6661) 
(list 4480.125 867.6764) 
(list 4480.125 867.6867) 
(list 4480.125 867.6969) 
(list 4480.125 867.7072) 
(list 4480.125 867.7175) 
(list 4480.125 867.7278) 
(list 4480.125 867.7381) 
(list 4480.125 867.7483) 
(list 4480.125 867.7586) 
(list 4480.125 867.7689) 
(list 4480.125 867.7792) 
(list 4480.125 867.7894) 
(list 4480.125 867.7997) 
(list 4480.125 867.81) 
(list 4480 867.81)))
(apply 'command (append '("pline") coords '("c")))
(setq tap14 (ssadd (entlast) tap14))
(command "_mirror" (entlast) "" "4480,900" "4480,901" "No")
(setq tap14 (ssadd (entlast) tap14))
(setq coords (list 
(list 4480.4362 867.44) 
(list 4480.4258 867.44) 
(list 4480.4258 867.4503) 
(list 4480.4253 867.4606) 
(list 4480.4242 867.4708) 
(list 4480.4226 867.4811) 
(list 4480.4205 867.4914) 
(list 4480.418 867.5017) 
(list 4480.4151 867.5119) 
(list 4480.412 867.5222) 
(list 4480.4086 867.5325) 
(list 4480.4052 867.5428) 
(list 4480.4017 867.5531) 
(list 4480.3985 867.5633) 
(list 4480.3954 867.5736) 
(list 4480.3927 867.5839) 
(list 4480.3904 867.5942) 
(list 4480.3887 867.6044) 
(list 4480.3875 867.6147) 
(list 4480.387 867.625) 
(list 4480.3871 867.6353) 
(list 4480.388 867.6456) 
(list 4480.3894 867.6558) 
(list 4480.3916 867.6661) 
(list 4480.3943 867.6764) 
(list 4480.3975 867.6867) 
(list 4480.4012 867.6969) 
(list 4480.4052 867.7072) 
(list 4480.4094 867.7175) 
(list 4480.4137 867.7278) 
(list 4480.4179 867.7381) 
(list 4480.422 867.7483) 
(list 4480.4258 867.7586) 
(list 4480.4291 867.7689) 
(list 4480.4319 867.7792) 
(list 4480.4341 867.7894) 
(list 4480.4355 867.7997) 
(list 4480.4362 867.81) 
(list 4480.4362 867.81)))
(apply 'command (append '("pline") coords '("c")))
(setq tap14 (ssadd (entlast) tap14))
(command "_mirror" (entlast) "" "4480,900" "4480,901" "No")
(setq tap14 (ssadd (entlast) tap14))
(setq coords (list 
(list 4481.122 867.44) 
(list 4480.4362 867.44) 
(list 4480.4362 867.4503) 
(list 4480.4362 867.4606) 
(list 4480.4362 867.4708) 
(list 4480.4362 867.4811) 
(list 4480.4362 867.4914) 
(list 4480.4362 867.5017) 
(list 4480.4362 867.5119) 
(list 4480.4362 867.5222) 
(list 4480.4362 867.5325) 
(list 4480.4362 867.5428) 
(list 4480.4362 867.5531) 
(list 4480.4362 867.5633) 
(list 4480.4362 867.5736) 
(list 4480.4362 867.5839) 
(list 4480.4362 867.5942) 
(list 4480.4362 867.6044) 
(list 4480.4362 867.6147) 
(list 4480.4362 867.625) 
(list 4480.4362 867.6353) 
(list 4480.4362 867.6456) 
(list 4480.4362 867.6558) 
(list 4480.4362 867.6661) 
(list 4480.4362 867.6764) 
(list 4480.4362 867.6867) 
(list 4480.4362 867.6969) 
(list 4480.4362 867.7072) 
(list 4480.4362 867.7175) 
(list 4480.4362 867.7278) 
(list 4480.4362 867.7381) 
(list 4480.4362 867.7483) 
(list 4480.4362 867.7586) 
(list 4480.4362 867.7689) 
(list 4480.4362 867.7792) 
(list 4480.4362 867.7894) 
(list 4480.4362 867.7997) 
(list 4480.4362 867.81) 
(list 4481.122 867.81)))
(apply 'command (append '("pline") coords '("c")))
(setq tap14 (ssadd (entlast) tap14))
(command "_mirror" (entlast) "" "4480,900" "4480,901" "No")
(setq tap14 (ssadd (entlast) tap14))
(setq coords (list 
(list 4480 867.81) 
(list 4480.125 867.81) 
(list 4480.125 867.8203) 
(list 4480.125 867.8306) 
(list 4480.125 867.8408) 
(list 4480.125 867.8511) 
(list 4480.125 867.8614) 
(list 4480.125 867.8717) 
(list 4480.125 867.8819) 
(list 4480.125 867.8922) 
(list 4480.125 867.9025) 
(list 4480.125 867.9128) 
(list 4480.125 867.9231) 
(list 4480.125 867.9333) 
(list 4480.125 867.9436) 
(list 4480.125 867.9539) 
(list 4480.125 867.9642) 
(list 4480.125 867.9744) 
(list 4480.125 867.9847) 
(list 4480.125 867.995) 
(list 4480.125 868.0053) 
(list 4480.125 868.0156) 
(list 4480.125 868.0258) 
(list 4480.125 868.0361) 
(list 4480.125 868.0464) 
(list 4480.125 868.0567) 
(list 4480.125 868.0669) 
(list 4480.125 868.0772) 
(list 4480.125 868.0875) 
(list 4480.125 868.0978) 
(list 4480.125 868.1081) 
(list 4480.125 868.1183) 
(list 4480.125 868.1286) 
(list 4480.125 868.1389) 
(list 4480.125 868.1492) 
(list 4480.125 868.1594) 
(list 4480.125 868.1697) 
(list 4480.125 868.18) 
(list 4480 868.18)))
(apply 'command (append '("pline") coords '("c")))
(setq tap14 (ssadd (entlast) tap14))
(command "_mirror" (entlast) "" "4480,900" "4480,901" "No")
(setq tap14 (ssadd (entlast) tap14))
(setq coords (list 
(list 4480.4466 867.81) 
(list 4480.4362 867.81) 
(list 4480.4361 867.8203) 
(list 4480.4352 867.8306) 
(list 4480.4334 867.8408) 
(list 4480.4309 867.8511) 
(list 4480.4278 867.8614) 
(list 4480.424 867.8717) 
(list 4480.4197 867.8819) 
(list 4480.4151 867.8922) 
(list 4480.4102 867.9025) 
(list 4480.4052 867.9128) 
(list 4480.4003 867.9231) 
(list 4480.3957 867.9333) 
(list 4480.3914 867.9436) 
(list 4480.3876 867.9539) 
(list 4480.3844 867.9642) 
(list 4480.382 867.9744) 
(list 4480.3805 867.9847) 
(list 4480.3798 867.995) 
(list 4480.3801 868.0053) 
(list 4480.3813 868.0156) 
(list 4480.3834 868.0258) 
(list 4480.3864 868.0361) 
(list 4480.3902 868.0464) 
(list 4480.3947 868.0567) 
(list 4480.3998 868.0669) 
(list 4480.4053 868.0772) 
(list 4480.411 868.0875) 
(list 4480.4168 868.0978) 
(list 4480.4225 868.1081) 
(list 4480.428 868.1183) 
(list 4480.433 868.1286) 
(list 4480.4374 868.1389) 
(list 4480.4411 868.1492) 
(list 4480.4439 868.1594) 
(list 4480.4458 868.1697) 
(list 4480.4466 868.18) 
(list 4480.4466 868.18)))
(apply 'command (append '("pline") coords '("c")))
(setq tap14 (ssadd (entlast) tap14))
(command "_mirror" (entlast) "" "4480,900" "4480,901" "No")
(setq tap14 (ssadd (entlast) tap14))
(setq coords (list 
(list 4481.122 867.81) 
(list 4480.4466 867.81) 
(list 4480.4466 867.8203) 
(list 4480.4466 867.8306) 
(list 4480.4466 867.8408) 
(list 4480.4466 867.8511) 
(list 4480.4466 867.8614) 
(list 4480.4466 867.8717) 
(list 4480.4466 867.8819) 
(list 4480.4466 867.8922) 
(list 4480.4466 867.9025) 
(list 4480.4466 867.9128) 
(list 4480.4466 867.9231) 
(list 4480.4466 867.9333) 
(list 4480.4466 867.9436) 
(list 4480.4466 867.9539) 
(list 4480.4466 867.9642) 
(list 4480.4466 867.9744) 
(list 4480.4466 867.9847) 
(list 4480.4466 867.995) 
(list 4480.4466 868.0053) 
(list 4480.4466 868.0156) 
(list 4480.4466 868.0258) 
(list 4480.4466 868.0361) 
(list 4480.4466 868.0464) 
(list 4480.4466 868.0567) 
(list 4480.4466 868.0669) 
(list 4480.4466 868.0772) 
(list 4480.4466 868.0875) 
(list 4480.4466 868.0978) 
(list 4480.4466 868.1081) 
(list 4480.4466 868.1183) 
(list 4480.4466 868.1286) 
(list 4480.4466 868.1389) 
(list 4480.4466 868.1492) 
(list 4480.4466 868.1594) 
(list 4480.4466 868.1697) 
(list 4480.4466 868.18) 
(list 4481.122 868.18)))
(apply 'command (append '("pline") coords '("c")))
(setq tap14 (ssadd (entlast) tap14))
(command "_mirror" (entlast) "" "4480,900" "4480,901" "No")
(setq tap14 (ssadd (entlast) tap14))
(setq coords (list 
(list 4480 868.18) 
(list 4480.125 868.18) 
(list 4480.125 868.1903) 
(list 4480.125 868.2006) 
(list 4480.125 868.2108) 
(list 4480.125 868.2211) 
(list 4480.125 868.2314) 
(list 4480.125 868.2417) 
(list 4480.125 868.2519) 
(list 4480.125 868.2622) 
(list 4480.125 868.2725) 
(list 4480.125 868.2828) 
(list 4480.125 868.2931) 
(list 4480.125 868.3033) 
(list 4480.125 868.3136) 
(list 4480.125 868.3239) 
(list 4480.125 868.3342) 
(list 4480.125 868.3444) 
(list 4480.125 868.3547) 
(list 4480.125 868.365) 
(list 4480.125 868.3753) 
(list 4480.125 868.3856) 
(list 4480.125 868.3958) 
(list 4480.125 868.4061) 
(list 4480.125 868.4164) 
(list 4480.125 868.4267) 
(list 4480.125 868.4369) 
(list 4480.125 868.4472) 
(list 4480.125 868.4575) 
(list 4480.125 868.4678) 
(list 4480.125 868.4781) 
(list 4480.125 868.4883) 
(list 4480.125 868.4986) 
(list 4480.125 868.5089) 
(list 4480.125 868.5192) 
(list 4480.125 868.5294) 
(list 4480.125 868.5397) 
(list 4480.125 868.55) 
(list 4480 868.55)))
(apply 'command (append '("pline") coords '("c")))
(setq tap14 (ssadd (entlast) tap14))
(command "_mirror" (entlast) "" "4480,900" "4480,901" "No")
(setq tap14 (ssadd (entlast) tap14))
(setq coords (list 
(list 4480.457 868.18) 
(list 4480.4466 868.18) 
(list 4480.4464 868.1903) 
(list 4480.445 868.2006) 
(list 4480.4427 868.2108) 
(list 4480.4393 868.2211) 
(list 4480.435 868.2314) 
(list 4480.43 868.2417) 
(list 4480.4243 868.2519) 
(list 4480.4182 868.2622) 
(list 4480.4118 868.2725) 
(list 4480.4053 868.2828) 
(list 4480.3989 868.2931) 
(list 4480.3929 868.3033) 
(list 4480.3873 868.3136) 
(list 4480.3824 868.3239) 
(list 4480.3784 868.3342) 
(list 4480.3754 868.3444) 
(list 4480.3734 868.3547) 
(list 4480.3726 868.365) 
(list 4480.373 868.3753) 
(list 4480.3746 868.3856) 
(list 4480.3774 868.3958) 
(list 4480.3813 868.4061) 
(list 4480.3862 868.4164) 
(list 4480.3919 868.4267) 
(list 4480.3984 868.4369) 
(list 4480.4053 868.4472) 
(list 4480.4126 868.4575) 
(list 4480.4199 868.4678) 
(list 4480.4272 868.4781) 
(list 4480.434 868.4883) 
(list 4480.4403 868.4986) 
(list 4480.4458 868.5089) 
(list 4480.4503 868.5192) 
(list 4480.4538 868.5294) 
(list 4480.456 868.5397) 
(list 4480.457 868.55) 
(list 4480.457 868.55)))
(apply 'command (append '("pline") coords '("c")))
(setq tap14 (ssadd (entlast) tap14))
(command "_mirror" (entlast) "" "4480,900" "4480,901" "No")
(setq tap14 (ssadd (entlast) tap14))
(setq coords (list 
(list 4481.122 868.18) 
(list 4480.457 868.18) 
(list 4480.457 868.1903) 
(list 4480.457 868.2006) 
(list 4480.457 868.2108) 
(list 4480.457 868.2211) 
(list 4480.457 868.2314) 
(list 4480.457 868.2417) 
(list 4480.457 868.2519) 
(list 4480.457 868.2622) 
(list 4480.457 868.2725) 
(list 4480.457 868.2828) 
(list 4480.457 868.2931) 
(list 4480.457 868.3033) 
(list 4480.457 868.3136) 
(list 4480.457 868.3239) 
(list 4480.457 868.3342) 
(list 4480.457 868.3444) 
(list 4480.457 868.3547) 
(list 4480.457 868.365) 
(list 4480.457 868.3753) 
(list 4480.457 868.3856) 
(list 4480.457 868.3958) 
(list 4480.457 868.4061) 
(list 4480.457 868.4164) 
(list 4480.457 868.4267) 
(list 4480.457 868.4369) 
(list 4480.457 868.4472) 
(list 4480.457 868.4575) 
(list 4480.457 868.4678) 
(list 4480.457 868.4781) 
(list 4480.457 868.4883) 
(list 4480.457 868.4986) 
(list 4480.457 868.5089) 
(list 4480.457 868.5192) 
(list 4480.457 868.5294) 
(list 4480.457 868.5397) 
(list 4480.457 868.55) 
(list 4481.122 868.55)))
(apply 'command (append '("pline") coords '("c")))
(setq tap14 (ssadd (entlast) tap14))
(command "_mirror" (entlast) "" "4480,900" "4480,901" "No")
(setq tap14 (ssadd (entlast) tap14))
(setq coords (list 
(list 4480 868.55) 
(list 4480.125 868.55) 
(list 4480.125 868.5603) 
(list 4480.125 868.5706) 
(list 4480.125 868.5808) 
(list 4480.125 868.5911) 
(list 4480.125 868.6014) 
(list 4480.125 868.6117) 
(list 4480.125 868.6219) 
(list 4480.125 868.6322) 
(list 4480.125 868.6425) 
(list 4480.125 868.6528) 
(list 4480.125 868.6631) 
(list 4480.125 868.6733) 
(list 4480.125 868.6836) 
(list 4480.125 868.6939) 
(list 4480.125 868.7042) 
(list 4480.125 868.7144) 
(list 4480.125 868.7247) 
(list 4480.125 868.735) 
(list 4480.125 868.7453) 
(list 4480.125 868.7556) 
(list 4480.125 868.7658) 
(list 4480.125 868.7761) 
(list 4480.125 868.7864) 
(list 4480.125 868.7967) 
(list 4480.125 868.8069) 
(list 4480.125 868.8172) 
(list 4480.125 868.8275) 
(list 4480.125 868.8378) 
(list 4480.125 868.8481) 
(list 4480.125 868.8583) 
(list 4480.125 868.8686) 
(list 4480.125 868.8789) 
(list 4480.125 868.8892) 
(list 4480.125 868.8994) 
(list 4480.125 868.9097) 
(list 4480.125 868.92) 
(list 4480 868.92)))
(apply 'command (append '("pline") coords '("c")))
(setq tap14 (ssadd (entlast) tap14))
(command "_mirror" (entlast) "" "4480,900" "4480,901" "No")
(setq tap14 (ssadd (entlast) tap14))
(setq coords (list 
(list 4480.4674 868.55) 
(list 4480.457 868.55) 
(list 4480.4566 868.5603) 
(list 4480.4549 868.5706) 
(list 4480.4519 868.5808) 
(list 4480.4476 868.5911) 
(list 4480.4423 868.6014) 
(list 4480.436 868.6117) 
(list 4480.4289 868.6219) 
(list 4480.4213 868.6322) 
(list 4480.4134 868.6425) 
(list 4480.4054 868.6528) 
(list 4480.3975 868.6631) 
(list 4480.3901 868.6733) 
(list 4480.3833 868.6836) 
(list 4480.3773 868.6939) 
(list 4480.3724 868.7042) 
(list 4480.3687 868.7144) 
(list 4480.3663 868.7247) 
(list 4480.3654 868.735) 
(list 4480.3659 868.7453) 
(list 4480.3679 868.7556) 
(list 4480.3714 868.7658) 
(list 4480.3762 868.7761) 
(list 4480.3821 868.7864) 
(list 4480.3891 868.7967) 
(list 4480.397 868.8069) 
(list 4480.4054 868.8172) 
(list 4480.4142 868.8275) 
(list 4480.4231 868.8378) 
(list 4480.4318 868.8481) 
(list 4480.44 868.8583) 
(list 4480.4475 868.8686) 
(list 4480.4541 868.8789) 
(list 4480.4596 868.8892) 
(list 4480.4637 868.8994) 
(list 4480.4663 868.9097) 
(list 4480.4674 868.92) 
(list 4480.4674 868.92)))
(apply 'command (append '("pline") coords '("c")))
(setq tap14 (ssadd (entlast) tap14))
(command "_mirror" (entlast) "" "4480,900" "4480,901" "No")
(setq tap14 (ssadd (entlast) tap14))
(setq coords (list 
(list 4481.122 868.55) 
(list 4480.4674 868.55) 
(list 4480.4674 868.5603) 
(list 4480.4674 868.5706) 
(list 4480.4674 868.5808) 
(list 4480.4674 868.5911) 
(list 4480.4674 868.6014) 
(list 4480.4674 868.6117) 
(list 4480.4674 868.6219) 
(list 4480.4674 868.6322) 
(list 4480.4674 868.6425) 
(list 4480.4674 868.6528) 
(list 4480.4674 868.6631) 
(list 4480.4674 868.6733) 
(list 4480.4674 868.6836) 
(list 4480.4674 868.6939) 
(list 4480.4674 868.7042) 
(list 4480.4674 868.7144) 
(list 4480.4674 868.7247) 
(list 4480.4674 868.735) 
(list 4480.4674 868.7453) 
(list 4480.4674 868.7556) 
(list 4480.4674 868.7658) 
(list 4480.4674 868.7761) 
(list 4480.4674 868.7864) 
(list 4480.4674 868.7967) 
(list 4480.4674 868.8069) 
(list 4480.4674 868.8172) 
(list 4480.4674 868.8275) 
(list 4480.4674 868.8378) 
(list 4480.4674 868.8481) 
(list 4480.4674 868.8583) 
(list 4480.4674 868.8686) 
(list 4480.4674 868.8789) 
(list 4480.4674 868.8892) 
(list 4480.4674 868.8994) 
(list 4480.4674 868.9097) 
(list 4480.4674 868.92) 
(list 4481.122 868.92)))
(apply 'command (append '("pline") coords '("c")))
(setq tap14 (ssadd (entlast) tap14))
(command "_mirror" (entlast) "" "4480,900" "4480,901" "No")
(setq tap14 (ssadd (entlast) tap14))
(setq coords (list 
(list 4480 868.92) 
(list 4480.125 868.92) 
(list 4480.125 868.9303) 
(list 4480.125 868.9406) 
(list 4480.125 868.9508) 
(list 4480.125 868.9611) 
(list 4480.125 868.9714) 
(list 4480.125 868.9817) 
(list 4480.125 868.9919) 
(list 4480.125 869.0022) 
(list 4480.125 869.0125) 
(list 4480.125 869.0228) 
(list 4480.125 869.0331) 
(list 4480.125 869.0433) 
(list 4480.125 869.0536) 
(list 4480.125 869.0639) 
(list 4480.125 869.0742) 
(list 4480.125 869.0844) 
(list 4480.125 869.0947) 
(list 4480.125 869.105) 
(list 4480.125 869.1153) 
(list 4480.125 869.1256) 
(list 4480.125 869.1358) 
(list 4480.125 869.1461) 
(list 4480.125 869.1564) 
(list 4480.125 869.1667) 
(list 4480.125 869.1769) 
(list 4480.125 869.1872) 
(list 4480.125 869.1975) 
(list 4480.125 869.2078) 
(list 4480.125 869.2181) 
(list 4480.125 869.2283) 
(list 4480.125 869.2386) 
(list 4480.125 869.2489) 
(list 4480.125 869.2592) 
(list 4480.125 869.2694) 
(list 4480.125 869.2797) 
(list 4480.125 869.29) 
(list 4480 869.29)))
(apply 'command (append '("pline") coords '("c")))
(setq tap14 (ssadd (entlast) tap14))
(command "_mirror" (entlast) "" "4480,900" "4480,901" "No")
(setq tap14 (ssadd (entlast) tap14))
(setq coords (list 
(list 4480.4778 868.92) 
(list 4480.4674 868.92) 
(list 4480.4669 868.9303) 
(list 4480.4648 868.9406) 
(list 4480.4611 868.9508) 
(list 4480.456 868.9611) 
(list 4480.4495 868.9714) 
(list 4480.442 868.9817) 
(list 4480.4336 868.9919) 
(list 4480.4245 869.0022) 
(list 4480.415 869.0125) 
(list 4480.4055 869.0228) 
(list 4480.3961 869.0331) 
(list 4480.3873 869.0433) 
(list 4480.3792 869.0536) 
(list 4480.3722 869.0639) 
(list 4480.3664 869.0742) 
(list 4480.362 869.0844) 
(list 4480.3593 869.0947) 
(list 4480.3582 869.105) 
(list 4480.3589 869.1153) 
(list 4480.3613 869.1256) 
(list 4480.3654 869.1358) 
(list 4480.371 869.1461) 
(list 4480.3781 869.1564) 
(list 4480.3863 869.1667) 
(list 4480.3956 869.1769) 
(list 4480.4055 869.1872) 
(list 4480.4158 869.1975) 
(list 4480.4262 869.2078) 
(list 4480.4364 869.2181) 
(list 4480.446 869.2283) 
(list 4480.4548 869.2386) 
(list 4480.4625 869.2489) 
(list 4480.4688 869.2592) 
(list 4480.4735 869.2694) 
(list 4480.4766 869.2797) 
(list 4480.4778 869.29) 
(list 4480.4778 869.29)))
(apply 'command (append '("pline") coords '("c")))
(setq tap14 (ssadd (entlast) tap14))
(command "_mirror" (entlast) "" "4480,900" "4480,901" "No")
(setq tap14 (ssadd (entlast) tap14))
(setq coords (list 
(list 4481.122 868.92) 
(list 4480.4778 868.92) 
(list 4480.4778 868.9303) 
(list 4480.4778 868.9406) 
(list 4480.4778 868.9508) 
(list 4480.4778 868.9611) 
(list 4480.4778 868.9714) 
(list 4480.4778 868.9817) 
(list 4480.4778 868.9919) 
(list 4480.4778 869.0022) 
(list 4480.4778 869.0125) 
(list 4480.4778 869.0228) 
(list 4480.4778 869.0331) 
(list 4480.4778 869.0433) 
(list 4480.4778 869.0536) 
(list 4480.4778 869.0639) 
(list 4480.4778 869.0742) 
(list 4480.4778 869.0844) 
(list 4480.4778 869.0947) 
(list 4480.4778 869.105) 
(list 4480.4778 869.1153) 
(list 4480.4778 869.1256) 
(list 4480.4778 869.1358) 
(list 4480.4778 869.1461) 
(list 4480.4778 869.1564) 
(list 4480.4778 869.1667) 
(list 4480.4778 869.1769) 
(list 4480.4778 869.1872) 
(list 4480.4778 869.1975) 
(list 4480.4778 869.2078) 
(list 4480.4778 869.2181) 
(list 4480.4778 869.2283) 
(list 4480.4778 869.2386) 
(list 4480.4778 869.2489) 
(list 4480.4778 869.2592) 
(list 4480.4778 869.2694) 
(list 4480.4778 869.2797) 
(list 4480.4778 869.29) 
(list 4481.122 869.29)))
(apply 'command (append '("pline") coords '("c")))
(setq tap14 (ssadd (entlast) tap14))
(command "_mirror" (entlast) "" "4480,900" "4480,901" "No")
(setq tap14 (ssadd (entlast) tap14))
(setq coords (list 
(list 4480 869.29) 
(list 4480.125 869.29) 
(list 4480.125 869.3003) 
(list 4480.125 869.3106) 
(list 4480.125 869.3208) 
(list 4480.125 869.3311) 
(list 4480.125 869.3414) 
(list 4480.125 869.3517) 
(list 4480.125 869.3619) 
(list 4480.125 869.3722) 
(list 4480.125 869.3825) 
(list 4480.125 869.3928) 
(list 4480.125 869.4031) 
(list 4480.125 869.4133) 
(list 4480.125 869.4236) 
(list 4480.125 869.4339) 
(list 4480.125 869.4442) 
(list 4480.125 869.4544) 
(list 4480.125 869.4647) 
(list 4480.125 869.475) 
(list 4480.125 869.4853) 
(list 4480.125 869.4956) 
(list 4480.125 869.5058) 
(list 4480.125 869.5161) 
(list 4480.125 869.5264) 
(list 4480.125 869.5367) 
(list 4480.125 869.5469) 
(list 4480.125 869.5572) 
(list 4480.125 869.5675) 
(list 4480.125 869.5778) 
(list 4480.125 869.5881) 
(list 4480.125 869.5983) 
(list 4480.125 869.6086) 
(list 4480.125 869.6189) 
(list 4480.125 869.6292) 
(list 4480.125 869.6394) 
(list 4480.125 869.6497) 
(list 4480.125 869.66) 
(list 4480 869.66)))
(apply 'command (append '("pline") coords '("c")))
(setq tap14 (ssadd (entlast) tap14))
(command "_mirror" (entlast) "" "4480,900" "4480,901" "No")
(setq tap14 (ssadd (entlast) tap14))
(setq coords (list 
(list 4480.4882 869.29) 
(list 4480.4778 869.29) 
(list 4480.4771 869.3003) 
(list 4480.4746 869.3106) 
(list 4480.4703 869.3208) 
(list 4480.4643 869.3311) 
(list 4480.4568 869.3414) 
(list 4480.448 869.3517) 
(list 4480.4382 869.3619) 
(list 4480.4276 869.3722) 
(list 4480.4166 869.3825) 
(list 4480.4055 869.3928) 
(list 4480.3947 869.4031) 
(list 4480.3845 869.4133) 
(list 4480.3751 869.4236) 
(list 4480.367 869.4339) 
(list 4480.3603 869.4442) 
(list 4480.3554 869.4544) 
(list 4480.3522 869.4647) 
(list 4480.351 869.475) 
(list 4480.3518 869.4853) 
(list 4480.3546 869.4956) 
(list 4480.3593 869.5058) 
(list 4480.3659 869.5161) 
(list 4480.374 869.5264) 
(list 4480.3835 869.5367) 
(list 4480.3942 869.5469) 
(list 4480.4056 869.5572) 
(list 4480.4174 869.5675) 
(list 4480.4293 869.5778) 
(list 4480.441 869.5881) 
(list 4480.452 869.5983) 
(list 4480.462 869.6086) 
(list 4480.4708 869.6189) 
(list 4480.478 869.6292) 
(list 4480.4834 869.6394) 
(list 4480.4868 869.6497) 
(list 4480.4882 869.66) 
(list 4480.4882 869.66)))
(apply 'command (append '("pline") coords '("c")))
(setq tap14 (ssadd (entlast) tap14))
(command "_mirror" (entlast) "" "4480,900" "4480,901" "No")
(setq tap14 (ssadd (entlast) tap14))
(setq coords (list 
(list 4481.122 869.29) 
(list 4480.4882 869.29) 
(list 4480.4882 869.3003) 
(list 4480.4882 869.3106) 
(list 4480.4882 869.3208) 
(list 4480.4882 869.3311) 
(list 4480.4882 869.3414) 
(list 4480.4882 869.3517) 
(list 4480.4882 869.3619) 
(list 4480.4882 869.3722) 
(list 4480.4882 869.3825) 
(list 4480.4882 869.3928) 
(list 4480.4882 869.4031) 
(list 4480.4882 869.4133) 
(list 4480.4882 869.4236) 
(list 4480.4882 869.4339) 
(list 4480.4882 869.4442) 
(list 4480.4882 869.4544) 
(list 4480.4882 869.4647) 
(list 4480.4882 869.475) 
(list 4480.4882 869.4853) 
(list 4480.4882 869.4956) 
(list 4480.4882 869.5058) 
(list 4480.4882 869.5161) 
(list 4480.4882 869.5264) 
(list 4480.4882 869.5367) 
(list 4480.4882 869.5469) 
(list 4480.4882 869.5572) 
(list 4480.4882 869.5675) 
(list 4480.4882 869.5778) 
(list 4480.4882 869.5881) 
(list 4480.4882 869.5983) 
(list 4480.4882 869.6086) 
(list 4480.4882 869.6189) 
(list 4480.4882 869.6292) 
(list 4480.4882 869.6394) 
(list 4480.4882 869.6497) 
(list 4480.4882 869.66) 
(list 4481.122 869.66)))
(apply 'command (append '("pline") coords '("c")))
(setq tap14 (ssadd (entlast) tap14))
(command "_mirror" (entlast) "" "4480,900" "4480,901" "No")
(setq tap14 (ssadd (entlast) tap14))
(setq coords (list 
(list 4480 869.66) 
(list 4480.125 869.66) 
(list 4480.125 869.6703) 
(list 4480.125 869.6806) 
(list 4480.125 869.6908) 
(list 4480.125 869.7011) 
(list 4480.125 869.7114) 
(list 4480.125 869.7217) 
(list 4480.125 869.7319) 
(list 4480.125 869.7422) 
(list 4480.125 869.7525) 
(list 4480.125 869.7628) 
(list 4480.125 869.7731) 
(list 4480.125 869.7833) 
(list 4480.125 869.7936) 
(list 4480.125 869.8039) 
(list 4480.125 869.8142) 
(list 4480.125 869.8244) 
(list 4480.125 869.8347) 
(list 4480.125 869.845) 
(list 4480.125 869.8553) 
(list 4480.125 869.8656) 
(list 4480.125 869.8758) 
(list 4480.125 869.8861) 
(list 4480.125 869.8964) 
(list 4480.125 869.9067) 
(list 4480.125 869.9169) 
(list 4480.125 869.9272) 
(list 4480.125 869.9375) 
(list 4480.125 869.9478) 
(list 4480.125 869.9581) 
(list 4480.125 869.9683) 
(list 4480.125 869.9786) 
(list 4480.125 869.9889) 
(list 4480.125 869.9992) 
(list 4480.125 870.0094) 
(list 4480.125 870.0197) 
(list 4480.125 870.03) 
(list 4480 870.03)))
(apply 'command (append '("pline") coords '("c")))
(setq tap14 (ssadd (entlast) tap14))
(command "_mirror" (entlast) "" "4480,900" "4480,901" "No")
(setq tap14 (ssadd (entlast) tap14))
(setq coords (list 
(list 4480.4986 869.66) 
(list 4480.4882 869.66) 
(list 4480.4874 869.6703) 
(list 4480.4845 869.6806) 
(list 4480.4795 869.6908) 
(list 4480.4727 869.7011) 
(list 4480.4641 869.7114) 
(list 4480.454 869.7217) 
(list 4480.4428 869.7319) 
(list 4480.4307 869.7422) 
(list 4480.4182 869.7525) 
(list 4480.4056 869.7628) 
(list 4480.3933 869.7731) 
(list 4480.3817 869.7833) 
(list 4480.3711 869.7936) 
(list 4480.3619 869.8039) 
(list 4480.3543 869.8142) 
(list 4480.3487 869.8244) 
(list 4480.3451 869.8347) 
(list 4480.3438 869.845) 
(list 4480.3447 869.8553) 
(list 4480.3479 869.8656) 
(list 4480.3533 869.8758) 
(list 4480.3607 869.8861) 
(list 4480.37 869.8964) 
(list 4480.3807 869.9067) 
(list 4480.3927 869.9169) 
(list 4480.4056 869.9272) 
(list 4480.419 869.9375) 
(list 4480.4325 869.9478) 
(list 4480.4456 869.9581) 
(list 4480.458 869.9683) 
(list 4480.4693 869.9786) 
(list 4480.4791 869.9889) 
(list 4480.4872 869.9992) 
(list 4480.4933 870.0094) 
(list 4480.4971 870.0197) 
(list 4480.4986 870.03) 
(list 4480.4986 870.03)))
(apply 'command (append '("pline") coords '("c")))
(setq tap14 (ssadd (entlast) tap14))
(command "_mirror" (entlast) "" "4480,900" "4480,901" "No")
(setq tap14 (ssadd (entlast) tap14))
(setq coords (list 
(list 4481.122 869.66) 
(list 4480.4986 869.66) 
(list 4480.4986 869.6703) 
(list 4480.4986 869.6806) 
(list 4480.4986 869.6908) 
(list 4480.4986 869.7011) 
(list 4480.4986 869.7114) 
(list 4480.4986 869.7217) 
(list 4480.4986 869.7319) 
(list 4480.4986 869.7422) 
(list 4480.4986 869.7525) 
(list 4480.4986 869.7628) 
(list 4480.4986 869.7731) 
(list 4480.4986 869.7833) 
(list 4480.4986 869.7936) 
(list 4480.4986 869.8039) 
(list 4480.4986 869.8142) 
(list 4480.4986 869.8244) 
(list 4480.4986 869.8347) 
(list 4480.4986 869.845) 
(list 4480.4986 869.8553) 
(list 4480.4986 869.8656) 
(list 4480.4986 869.8758) 
(list 4480.4986 869.8861) 
(list 4480.4986 869.8964) 
(list 4480.4986 869.9067) 
(list 4480.4986 869.9169) 
(list 4480.4986 869.9272) 
(list 4480.4986 869.9375) 
(list 4480.4986 869.9478) 
(list 4480.4986 869.9581) 
(list 4480.4986 869.9683) 
(list 4480.4986 869.9786) 
(list 4480.4986 869.9889) 
(list 4480.4986 869.9992) 
(list 4480.4986 870.0094) 
(list 4480.4986 870.0197) 
(list 4480.4986 870.03) 
(list 4481.122 870.03)))
(apply 'command (append '("pline") coords '("c")))
(setq tap14 (ssadd (entlast) tap14))
(command "_mirror" (entlast) "" "4480,900" "4480,901" "No")
(setq tap14 (ssadd (entlast) tap14))
(setq coords (list 
(list 4480 870.03) 
(list 4480.125 870.03) 
(list 4480.125 870.0403) 
(list 4480.125 870.0506) 
(list 4480.125 870.0608) 
(list 4480.125 870.0711) 
(list 4480.125 870.0814) 
(list 4480.125 870.0917) 
(list 4480.125 870.1019) 
(list 4480.125 870.1122) 
(list 4480.125 870.1225) 
(list 4480.125 870.1328) 
(list 4480.125 870.1431) 
(list 4480.125 870.1533) 
(list 4480.125 870.1636) 
(list 4480.125 870.1739) 
(list 4480.125 870.1842) 
(list 4480.125 870.1944) 
(list 4480.125 870.2047) 
(list 4480.125 870.215) 
(list 4480.125 870.2253) 
(list 4480.125 870.2356) 
(list 4480.125 870.2458) 
(list 4480.125 870.2561) 
(list 4480.125 870.2664) 
(list 4480.125 870.2767) 
(list 4480.125 870.2869) 
(list 4480.125 870.2972) 
(list 4480.125 870.3075) 
(list 4480.125 870.3178) 
(list 4480.125 870.3281) 
(list 4480.125 870.3383) 
(list 4480.125 870.3486) 
(list 4480.125 870.3589) 
(list 4480.125 870.3692) 
(list 4480.125 870.3794) 
(list 4480.125 870.3897) 
(list 4480.125 870.4) 
(list 4480 870.4)))
(apply 'command (append '("pline") coords '("c")))
(setq tap14 (ssadd (entlast) tap14))
(command "_mirror" (entlast) "" "4480,900" "4480,901" "No")
(setq tap14 (ssadd (entlast) tap14))
(setq coords (list 
(list 4480.509 870.03) 
(list 4480.4986 870.03) 
(list 4480.4977 870.0403) 
(list 4480.4944 870.0506) 
(list 4480.4888 870.0608) 
(list 4480.481 870.0711) 
(list 4480.4713 870.0814) 
(list 4480.46 870.0917) 
(list 4480.4474 870.1019) 
(list 4480.4338 870.1122) 
(list 4480.4198 870.1225) 
(list 4480.4057 870.1328) 
(list 4480.3919 870.1431) 
(list 4480.3789 870.1533) 
(list 4480.367 870.1636) 
(list 4480.3567 870.1739) 
(list 4480.3483 870.1842) 
(list 4480.342 870.1944) 
(list 4480.3381 870.2047) 
(list 4480.3366 870.215) 
(list 4480.3377 870.2253) 
(list 4480.3413 870.2356) 
(list 4480.3473 870.2458) 
(list 4480.3556 870.2561) 
(list 4480.3659 870.2664) 
(list 4480.3779 870.2767) 
(list 4480.3913 870.2869) 
(list 4480.4057 870.2972) 
(list 4480.4206 870.3075) 
(list 4480.4356 870.3178) 
(list 4480.4502 870.3281) 
(list 4480.464 870.3383) 
(list 4480.4766 870.3486) 
(list 4480.4875 870.3589) 
(list 4480.4964 870.3692) 
(list 4480.5031 870.3794) 
(list 4480.5074 870.3897) 
(list 4480.509 870.4) 
(list 4480.509 870.4)))
(apply 'command (append '("pline") coords '("c")))
(setq tap14 (ssadd (entlast) tap14))
(command "_mirror" (entlast) "" "4480,900" "4480,901" "No")
(setq tap14 (ssadd (entlast) tap14))
(setq coords (list 
(list 4481.122 870.03) 
(list 4480.509 870.03) 
(list 4480.509 870.0403) 
(list 4480.509 870.0506) 
(list 4480.509 870.0608) 
(list 4480.509 870.0711) 
(list 4480.509 870.0814) 
(list 4480.509 870.0917) 
(list 4480.509 870.1019) 
(list 4480.509 870.1122) 
(list 4480.509 870.1225) 
(list 4480.509 870.1328) 
(list 4480.509 870.1431) 
(list 4480.509 870.1533) 
(list 4480.509 870.1636) 
(list 4480.509 870.1739) 
(list 4480.509 870.1842) 
(list 4480.509 870.1944) 
(list 4480.509 870.2047) 
(list 4480.509 870.215) 
(list 4480.509 870.2253) 
(list 4480.509 870.2356) 
(list 4480.509 870.2458) 
(list 4480.509 870.2561) 
(list 4480.509 870.2664) 
(list 4480.509 870.2767) 
(list 4480.509 870.2869) 
(list 4480.509 870.2972) 
(list 4480.509 870.3075) 
(list 4480.509 870.3178) 
(list 4480.509 870.3281) 
(list 4480.509 870.3383) 
(list 4480.509 870.3486) 
(list 4480.509 870.3589) 
(list 4480.509 870.3692) 
(list 4480.509 870.3794) 
(list 4480.509 870.3897) 
(list 4480.509 870.4) 
(list 4481.122 870.4)))
(apply 'command (append '("pline") coords '("c")))
(setq tap14 (ssadd (entlast) tap14))
(command "_mirror" (entlast) "" "4480,900" "4480,901" "No")
(setq tap14 (ssadd (entlast) tap14))
(setq coords (list 
(list 4480 870.4) 
(list 4480.125 870.4) 
(list 4480.125 870.4103) 
(list 4480.125 870.4206) 
(list 4480.125 870.4308) 
(list 4480.125 870.4411) 
(list 4480.125 870.4514) 
(list 4480.125 870.4617) 
(list 4480.125 870.4719) 
(list 4480.125 870.4822) 
(list 4480.125 870.4925) 
(list 4480.125 870.5028) 
(list 4480.125 870.5131) 
(list 4480.125 870.5233) 
(list 4480.125 870.5336) 
(list 4480.125 870.5439) 
(list 4480.125 870.5542) 
(list 4480.125 870.5644) 
(list 4480.125 870.5747) 
(list 4480.125 870.585) 
(list 4480.125 870.5953) 
(list 4480.125 870.6056) 
(list 4480.125 870.6158) 
(list 4480.125 870.6261) 
(list 4480.125 870.6364) 
(list 4480.125 870.6467) 
(list 4480.125 870.6569) 
(list 4480.125 870.6672) 
(list 4480.125 870.6775) 
(list 4480.125 870.6878) 
(list 4480.125 870.6981) 
(list 4480.125 870.7083) 
(list 4480.125 870.7186) 
(list 4480.125 870.7289) 
(list 4480.125 870.7392) 
(list 4480.125 870.7494) 
(list 4480.125 870.7597) 
(list 4480.125 870.77) 
(list 4480 870.77)))
(apply 'command (append '("pline") coords '("c")))
(setq tap14 (ssadd (entlast) tap14))
(command "_mirror" (entlast) "" "4480,900" "4480,901" "No")
(setq tap14 (ssadd (entlast) tap14))
(setq coords (list 
(list 4480.5194 870.4) 
(list 4480.509 870.4) 
(list 4480.5079 870.4103) 
(list 4480.5042 870.4206) 
(list 4480.498 870.4308) 
(list 4480.4893 870.4411) 
(list 4480.4786 870.4514) 
(list 4480.466 870.4617) 
(list 4480.452 870.4719) 
(list 4480.437 870.4822) 
(list 4480.4214 870.4925) 
(list 4480.4057 870.5028) 
(list 4480.3905 870.5131) 
(list 4480.3761 870.5233) 
(list 4480.363 870.5336) 
(list 4480.3516 870.5439) 
(list 4480.3423 870.5542) 
(list 4480.3353 870.5644) 
(list 4480.331 870.5747) 
(list 4480.3294 870.585) 
(list 4480.3306 870.5953) 
(list 4480.3346 870.6056) 
(list 4480.3413 870.6158) 
(list 4480.3504 870.6261) 
(list 4480.3618 870.6364) 
(list 4480.3751 870.6467) 
(list 4480.3899 870.6569) 
(list 4480.4058 870.6672) 
(list 4480.4222 870.6775) 
(list 4480.4387 870.6878) 
(list 4480.4548 870.6981) 
(list 4480.47 870.7083) 
(list 4480.4838 870.7186) 
(list 4480.4958 870.7289) 
(list 4480.5057 870.7392) 
(list 4480.513 870.7494) 
(list 4480.5176 870.7597) 
(list 4480.5194 870.77) 
(list 4480.5194 870.77)))
(apply 'command (append '("pline") coords '("c")))
(setq tap14 (ssadd (entlast) tap14))
(command "_mirror" (entlast) "" "4480,900" "4480,901" "No")
(setq tap14 (ssadd (entlast) tap14))
(setq coords (list 
(list 4481.122 870.4) 
(list 4480.5194 870.4) 
(list 4480.5194 870.4103) 
(list 4480.5194 870.4206) 
(list 4480.5194 870.4308) 
(list 4480.5194 870.4411) 
(list 4480.5194 870.4514) 
(list 4480.5194 870.4617) 
(list 4480.5194 870.4719) 
(list 4480.5194 870.4822) 
(list 4480.5194 870.4925) 
(list 4480.5194 870.5028) 
(list 4480.5194 870.5131) 
(list 4480.5194 870.5233) 
(list 4480.5194 870.5336) 
(list 4480.5194 870.5439) 
(list 4480.5194 870.5542) 
(list 4480.5194 870.5644) 
(list 4480.5194 870.5747) 
(list 4480.5194 870.585) 
(list 4480.5194 870.5953) 
(list 4480.5194 870.6056) 
(list 4480.5194 870.6158) 
(list 4480.5194 870.6261) 
(list 4480.5194 870.6364) 
(list 4480.5194 870.6467) 
(list 4480.5194 870.6569) 
(list 4480.5194 870.6672) 
(list 4480.5194 870.6775) 
(list 4480.5194 870.6878) 
(list 4480.5194 870.6981) 
(list 4480.5194 870.7083) 
(list 4480.5194 870.7186) 
(list 4480.5194 870.7289) 
(list 4480.5194 870.7392) 
(list 4480.5194 870.7494) 
(list 4480.5194 870.7597) 
(list 4480.5194 870.77) 
(list 4481.122 870.77)))
(apply 'command (append '("pline") coords '("c")))
(setq tap14 (ssadd (entlast) tap14))
(command "_mirror" (entlast) "" "4480,900" "4480,901" "No")
(setq tap14 (ssadd (entlast) tap14))
(setq coords (list 
(list 4480 870.77) 
(list 4480.125 870.77) 
(list 4480.125 870.7803) 
(list 4480.125 870.7906) 
(list 4480.125 870.8008) 
(list 4480.125 870.8111) 
(list 4480.125 870.8214) 
(list 4480.125 870.8317) 
(list 4480.125 870.8419) 
(list 4480.125 870.8522) 
(list 4480.125 870.8625) 
(list 4480.125 870.8728) 
(list 4480.125 870.8831) 
(list 4480.125 870.8933) 
(list 4480.125 870.9036) 
(list 4480.125 870.9139) 
(list 4480.125 870.9242) 
(list 4480.125 870.9344) 
(list 4480.125 870.9447) 
(list 4480.125 870.955) 
(list 4480.125 870.9653) 
(list 4480.125 870.9756) 
(list 4480.125 870.9858) 
(list 4480.125 870.9961) 
(list 4480.125 871.0064) 
(list 4480.125 871.0167) 
(list 4480.125 871.0269) 
(list 4480.125 871.0372) 
(list 4480.125 871.0475) 
(list 4480.125 871.0578) 
(list 4480.125 871.0681) 
(list 4480.125 871.0783) 
(list 4480.125 871.0886) 
(list 4480.125 871.0989) 
(list 4480.125 871.1092) 
(list 4480.125 871.1194) 
(list 4480.125 871.1297) 
(list 4480.125 871.14) 
(list 4480 871.14)))
(apply 'command (append '("pline") coords '("c")))
(setq tap14 (ssadd (entlast) tap14))
(command "_mirror" (entlast) "" "4480,900" "4480,901" "No")
(setq tap14 (ssadd (entlast) tap14))
(setq coords (list 
(list 4480.5298 870.77) 
(list 4480.5194 870.77) 
(list 4480.5182 870.7803) 
(list 4480.5141 870.7906) 
(list 4480.5072 870.8008) 
(list 4480.4977 870.8111) 
(list 4480.4858 870.8214) 
(list 4480.472 870.8317) 
(list 4480.4566 870.8419) 
(list 4480.4401 870.8522) 
(list 4480.423 870.8625) 
(list 4480.4058 870.8728) 
(list 4480.3891 870.8831) 
(list 4480.3733 870.8933) 
(list 4480.3589 870.9036) 
(list 4480.3464 870.9139) 
(list 4480.3363 870.9242) 
(list 4480.3287 870.9344) 
(list 4480.3239 870.9447) 
(list 4480.3222 870.955) 
(list 4480.3235 870.9653) 
(list 4480.3279 870.9756) 
(list 4480.3353 870.9858) 
(list 4480.3453 870.9961) 
(list 4480.3578 871.0064) 
(list 4480.3723 871.0167) 
(list 4480.3885 871.0269) 
(list 4480.4058 871.0372) 
(list 4480.4238 871.0475) 
(list 4480.4418 871.0578) 
(list 4480.4594 871.0681) 
(list 4480.476 871.0783) 
(list 4480.4911 871.0886) 
(list 4480.5042 871.0989) 
(list 4480.5149 871.1092) 
(list 4480.5229 871.1194) 
(list 4480.5279 871.1297) 
(list 4480.5298 871.14) 
(list 4480.5298 871.14)))
(apply 'command (append '("pline") coords '("c")))
(setq tap14 (ssadd (entlast) tap14))
(command "_mirror" (entlast) "" "4480,900" "4480,901" "No")
(setq tap14 (ssadd (entlast) tap14))
(setq coords (list 
(list 4481.122 870.77) 
(list 4480.5298 870.77) 
(list 4480.5298 870.7803) 
(list 4480.5298 870.7906) 
(list 4480.5298 870.8008) 
(list 4480.5298 870.8111) 
(list 4480.5298 870.8214) 
(list 4480.5298 870.8317) 
(list 4480.5298 870.8419) 
(list 4480.5298 870.8522) 
(list 4480.5298 870.8625) 
(list 4480.5298 870.8728) 
(list 4480.5298 870.8831) 
(list 4480.5298 870.8933) 
(list 4480.5298 870.9036) 
(list 4480.5298 870.9139) 
(list 4480.5298 870.9242) 
(list 4480.5298 870.9344) 
(list 4480.5298 870.9447) 
(list 4480.5298 870.955) 
(list 4480.5298 870.9653) 
(list 4480.5298 870.9756) 
(list 4480.5298 870.9858) 
(list 4480.5298 870.9961) 
(list 4480.5298 871.0064) 
(list 4480.5298 871.0167) 
(list 4480.5298 871.0269) 
(list 4480.5298 871.0372) 
(list 4480.5298 871.0475) 
(list 4480.5298 871.0578) 
(list 4480.5298 871.0681) 
(list 4480.5298 871.0783) 
(list 4480.5298 871.0886) 
(list 4480.5298 871.0989) 
(list 4480.5298 871.1092) 
(list 4480.5298 871.1194) 
(list 4480.5298 871.1297) 
(list 4480.5298 871.14) 
(list 4481.122 871.14)))
(apply 'command (append '("pline") coords '("c")))
(setq tap14 (ssadd (entlast) tap14))
(command "_mirror" (entlast) "" "4480,900" "4480,901" "No")
(setq tap14 (ssadd (entlast) tap14))
(setq coords (list 
(list 4480 871.14) 
(list 4480.125 871.14) 
(list 4480.125 871.1503) 
(list 4480.125 871.1606) 
(list 4480.125 871.1708) 
(list 4480.125 871.1811) 
(list 4480.125 871.1914) 
(list 4480.125 871.2017) 
(list 4480.125 871.2119) 
(list 4480.125 871.2222) 
(list 4480.125 871.2325) 
(list 4480.125 871.2428) 
(list 4480.125 871.2531) 
(list 4480.125 871.2633) 
(list 4480.125 871.2736) 
(list 4480.125 871.2839) 
(list 4480.125 871.2942) 
(list 4480.125 871.3044) 
(list 4480.125 871.3147) 
(list 4480.125 871.325) 
(list 4480.125 871.3353) 
(list 4480.125 871.3456) 
(list 4480.125 871.3558) 
(list 4480.125 871.3661) 
(list 4480.125 871.3764) 
(list 4480.125 871.3867) 
(list 4480.125 871.3969) 
(list 4480.125 871.4072) 
(list 4480.125 871.4175) 
(list 4480.125 871.4278) 
(list 4480.125 871.4381) 
(list 4480.125 871.4483) 
(list 4480.125 871.4586) 
(list 4480.125 871.4689) 
(list 4480.125 871.4792) 
(list 4480.125 871.4894) 
(list 4480.125 871.4997) 
(list 4480.125 871.51) 
(list 4480 871.51)))
(apply 'command (append '("pline") coords '("c")))
(setq tap14 (ssadd (entlast) tap14))
(command "_mirror" (entlast) "" "4480,900" "4480,901" "No")
(setq tap14 (ssadd (entlast) tap14))
(setq coords (list 
(list 4480.5402 871.14) 
(list 4480.5298 871.14) 
(list 4480.5285 871.1503) 
(list 4480.524 871.1606) 
(list 4480.5164 871.1708) 
(list 4480.506 871.1811) 
(list 4480.4931 871.1914) 
(list 4480.478 871.2017) 
(list 4480.4612 871.2119) 
(list 4480.4432 871.2222) 
(list 4480.4246 871.2325) 
(list 4480.4059 871.2428) 
(list 4480.3877 871.2531) 
(list 4480.3705 871.2633) 
(list 4480.3549 871.2736) 
(list 4480.3413 871.2839) 
(list 4480.3302 871.2942) 
(list 4480.322 871.3044) 
(list 4480.3169 871.3147) 
(list 4480.315 871.325) 
(list 4480.3165 871.3353) 
(list 4480.3213 871.3456) 
(list 4480.3292 871.3558) 
(list 4480.3402 871.3661) 
(list 4480.3537 871.3764) 
(list 4480.3695 871.3867) 
(list 4480.3871 871.3969) 
(list 4480.4059 871.4072) 
(list 4480.4254 871.4175) 
(list 4480.445 871.4278) 
(list 4480.464 871.4381) 
(list 4480.482 871.4483) 
(list 4480.4983 871.4586) 
(list 4480.5125 871.4689) 
(list 4480.5241 871.4792) 
(list 4480.5328 871.4894) 
(list 4480.5382 871.4997) 
(list 4480.5402 871.51) 
(list 4480.5402 871.51)))
(apply 'command (append '("pline") coords '("c")))
(setq tap14 (ssadd (entlast) tap14))
(command "_mirror" (entlast) "" "4480,900" "4480,901" "No")
(setq tap14 (ssadd (entlast) tap14))
(setq coords (list 
(list 4481.122 871.14) 
(list 4480.5402 871.14) 
(list 4480.5402 871.1503) 
(list 4480.5402 871.1606) 
(list 4480.5402 871.1708) 
(list 4480.5402 871.1811) 
(list 4480.5402 871.1914) 
(list 4480.5402 871.2017) 
(list 4480.5402 871.2119) 
(list 4480.5402 871.2222) 
(list 4480.5402 871.2325) 
(list 4480.5402 871.2428) 
(list 4480.5402 871.2531) 
(list 4480.5402 871.2633) 
(list 4480.5402 871.2736) 
(list 4480.5402 871.2839) 
(list 4480.5402 871.2942) 
(list 4480.5402 871.3044) 
(list 4480.5402 871.3147) 
(list 4480.5402 871.325) 
(list 4480.5402 871.3353) 
(list 4480.5402 871.3456) 
(list 4480.5402 871.3558) 
(list 4480.5402 871.3661) 
(list 4480.5402 871.3764) 
(list 4480.5402 871.3867) 
(list 4480.5402 871.3969) 
(list 4480.5402 871.4072) 
(list 4480.5402 871.4175) 
(list 4480.5402 871.4278) 
(list 4480.5402 871.4381) 
(list 4480.5402 871.4483) 
(list 4480.5402 871.4586) 
(list 4480.5402 871.4689) 
(list 4480.5402 871.4792) 
(list 4480.5402 871.4894) 
(list 4480.5402 871.4997) 
(list 4480.5402 871.51) 
(list 4481.122 871.51)))
(apply 'command (append '("pline") coords '("c")))
(setq tap14 (ssadd (entlast) tap14))
(command "_mirror" (entlast) "" "4480,900" "4480,901" "No")
(setq tap14 (ssadd (entlast) tap14))
(setq coords (list 
(list 4480 871.51) 
(list 4480.125 871.51) 
(list 4480.125 871.5203) 
(list 4480.125 871.5306) 
(list 4480.125 871.5408) 
(list 4480.125 871.5511) 
(list 4480.125 871.5614) 
(list 4480.125 871.5717) 
(list 4480.125 871.5819) 
(list 4480.125 871.5922) 
(list 4480.125 871.6025) 
(list 4480.125 871.6128) 
(list 4480.125 871.6231) 
(list 4480.125 871.6333) 
(list 4480.125 871.6436) 
(list 4480.125 871.6539) 
(list 4480.125 871.6642) 
(list 4480.125 871.6744) 
(list 4480.125 871.6847) 
(list 4480.125 871.695) 
(list 4480.125 871.7053) 
(list 4480.125 871.7156) 
(list 4480.125 871.7258) 
(list 4480.125 871.7361) 
(list 4480.125 871.7464) 
(list 4480.125 871.7567) 
(list 4480.125 871.7669) 
(list 4480.125 871.7772) 
(list 4480.125 871.7875) 
(list 4480.125 871.7978) 
(list 4480.125 871.8081) 
(list 4480.125 871.8183) 
(list 4480.125 871.8286) 
(list 4480.125 871.8389) 
(list 4480.125 871.8492) 
(list 4480.125 871.8594) 
(list 4480.125 871.8697) 
(list 4480.125 871.88) 
(list 4480 871.88)))
(apply 'command (append '("pline") coords '("c")))
(setq tap14 (ssadd (entlast) tap14))
(command "_mirror" (entlast) "" "4480,900" "4480,901" "No")
(setq tap14 (ssadd (entlast) tap14))
(setq coords (list 
(list 4480.5506 871.51) 
(list 4480.5402 871.51) 
(list 4480.5387 871.5203) 
(list 4480.5338 871.5306) 
(list 4480.5256 871.5408) 
(list 4480.5144 871.5511) 
(list 4480.5003 871.5614) 
(list 4480.484 871.5717) 
(list 4480.4658 871.5819) 
(list 4480.4464 871.5922) 
(list 4480.4262 871.6025) 
(list 4480.406 871.6128) 
(list 4480.3862 871.6231) 
(list 4480.3677 871.6333) 
(list 4480.3508 871.6436) 
(list 4480.3362 871.6539) 
(list 4480.3242 871.6642) 
(list 4480.3153 871.6744) 
(list 4480.3098 871.6847) 
(list 4480.3078 871.695) 
(list 4480.3094 871.7053) 
(list 4480.3146 871.7156) 
(list 4480.3232 871.7258) 
(list 4480.335 871.7361) 
(list 4480.3497 871.7464) 
(list 4480.3667 871.7567) 
(list 4480.3857 871.7669) 
(list 4480.406 871.7772) 
(list 4480.427 871.7875) 
(list 4480.4481 871.7978) 
(list 4480.4686 871.8081) 
(list 4480.488 871.8183) 
(list 4480.5056 871.8286) 
(list 4480.5208 871.8389) 
(list 4480.5333 871.8492) 
(list 4480.5426 871.8594) 
(list 4480.5484 871.8697) 
(list 4480.5506 871.88) 
(list 4480.5506 871.88)))
(apply 'command (append '("pline") coords '("c")))
(setq tap14 (ssadd (entlast) tap14))
(command "_mirror" (entlast) "" "4480,900" "4480,901" "No")
(setq tap14 (ssadd (entlast) tap14))
(setq coords (list 
(list 4481.122 871.51) 
(list 4480.5506 871.51) 
(list 4480.5506 871.5203) 
(list 4480.5506 871.5306) 
(list 4480.5506 871.5408) 
(list 4480.5506 871.5511) 
(list 4480.5506 871.5614) 
(list 4480.5506 871.5717) 
(list 4480.5506 871.5819) 
(list 4480.5506 871.5922) 
(list 4480.5506 871.6025) 
(list 4480.5506 871.6128) 
(list 4480.5506 871.6231) 
(list 4480.5506 871.6333) 
(list 4480.5506 871.6436) 
(list 4480.5506 871.6539) 
(list 4480.5506 871.6642) 
(list 4480.5506 871.6744) 
(list 4480.5506 871.6847) 
(list 4480.5506 871.695) 
(list 4480.5506 871.7053) 
(list 4480.5506 871.7156) 
(list 4480.5506 871.7258) 
(list 4480.5506 871.7361) 
(list 4480.5506 871.7464) 
(list 4480.5506 871.7567) 
(list 4480.5506 871.7669) 
(list 4480.5506 871.7772) 
(list 4480.5506 871.7875) 
(list 4480.5506 871.7978) 
(list 4480.5506 871.8081) 
(list 4480.5506 871.8183) 
(list 4480.5506 871.8286) 
(list 4480.5506 871.8389) 
(list 4480.5506 871.8492) 
(list 4480.5506 871.8594) 
(list 4480.5506 871.8697) 
(list 4480.5506 871.88) 
(list 4481.122 871.88)))
(apply 'command (append '("pline") coords '("c")))
(setq tap14 (ssadd (entlast) tap14))
(command "_mirror" (entlast) "" "4480,900" "4480,901" "No")
(setq tap14 (ssadd (entlast) tap14))
(setq coords (list 
(list 4480 871.88) 
(list 4480.125 871.88) 
(list 4480.125 871.8903) 
(list 4480.125 871.9006) 
(list 4480.125 871.9108) 
(list 4480.125 871.9211) 
(list 4480.125 871.9314) 
(list 4480.125 871.9417) 
(list 4480.125 871.9519) 
(list 4480.125 871.9622) 
(list 4480.125 871.9725) 
(list 4480.125 871.9828) 
(list 4480.125 871.9931) 
(list 4480.125 872.0033) 
(list 4480.125 872.0136) 
(list 4480.125 872.0239) 
(list 4480.125 872.0342) 
(list 4480.125 872.0444) 
(list 4480.125 872.0547) 
(list 4480.125 872.065) 
(list 4480.125 872.0753) 
(list 4480.125 872.0856) 
(list 4480.125 872.0958) 
(list 4480.125 872.1061) 
(list 4480.125 872.1164) 
(list 4480.125 872.1267) 
(list 4480.125 872.1369) 
(list 4480.125 872.1472) 
(list 4480.125 872.1575) 
(list 4480.125 872.1678) 
(list 4480.125 872.1781) 
(list 4480.125 872.1883) 
(list 4480.125 872.1986) 
(list 4480.125 872.2089) 
(list 4480.125 872.2192) 
(list 4480.125 872.2294) 
(list 4480.125 872.2397) 
(list 4480.125 872.25) 
(list 4480 872.25)))
(apply 'command (append '("pline") coords '("c")))
(setq tap14 (ssadd (entlast) tap14))
(command "_mirror" (entlast) "" "4480,900" "4480,901" "No")
(setq tap14 (ssadd (entlast) tap14))
(setq coords (list 
(list 4480.561 871.88) 
(list 4480.5506 871.88) 
(list 4480.549 871.8903) 
(list 4480.5437 871.9006) 
(list 4480.5349 871.9108) 
(list 4480.5227 871.9211) 
(list 4480.5076 871.9314) 
(list 4480.49 871.9417) 
(list 4480.4704 871.9519) 
(list 4480.4495 871.9622) 
(list 4480.4278 871.9725) 
(list 4480.406 871.9828) 
(list 4480.3848 871.9931) 
(list 4480.3649 872.0033) 
(list 4480.3467 872.0136) 
(list 4480.331 872.0239) 
(list 4480.3182 872.0342) 
(list 4480.3087 872.0444) 
(list 4480.3027 872.0547) 
(list 4480.3006 872.065) 
(list 4480.3023 872.0753) 
(list 4480.3079 872.0856) 
(list 4480.3172 872.0958) 
(list 4480.3299 872.1061) 
(list 4480.3456 872.1164) 
(list 4480.3639 872.1267) 
(list 4480.3843 872.1369) 
(list 4480.4061 872.1472) 
(list 4480.4286 872.1575) 
(list 4480.4512 872.1678) 
(list 4480.4733 872.1781) 
(list 4480.494 872.1883) 
(list 4480.5128 872.1986) 
(list 4480.5292 872.2089) 
(list 4480.5425 872.2192) 
(list 4480.5525 872.2294) 
(list 4480.5587 872.2397) 
(list 4480.561 872.25) 
(list 4480.561 872.25)))
(apply 'command (append '("pline") coords '("c")))
(setq tap14 (ssadd (entlast) tap14))
(command "_mirror" (entlast) "" "4480,900" "4480,901" "No")
(setq tap14 (ssadd (entlast) tap14))
(setq coords (list 
(list 4481.122 871.88) 
(list 4480.561 871.88) 
(list 4480.561 871.8903) 
(list 4480.561 871.9006) 
(list 4480.561 871.9108) 
(list 4480.561 871.9211) 
(list 4480.561 871.9314) 
(list 4480.561 871.9417) 
(list 4480.561 871.9519) 
(list 4480.561 871.9622) 
(list 4480.561 871.9725) 
(list 4480.561 871.9828) 
(list 4480.561 871.9931) 
(list 4480.561 872.0033) 
(list 4480.561 872.0136) 
(list 4480.561 872.0239) 
(list 4480.561 872.0342) 
(list 4480.561 872.0444) 
(list 4480.561 872.0547) 
(list 4480.561 872.065) 
(list 4480.561 872.0753) 
(list 4480.561 872.0856) 
(list 4480.561 872.0958) 
(list 4480.561 872.1061) 
(list 4480.561 872.1164) 
(list 4480.561 872.1267) 
(list 4480.561 872.1369) 
(list 4480.561 872.1472) 
(list 4480.561 872.1575) 
(list 4480.561 872.1678) 
(list 4480.561 872.1781) 
(list 4480.561 872.1883) 
(list 4480.561 872.1986) 
(list 4480.561 872.2089) 
(list 4480.561 872.2192) 
(list 4480.561 872.2294) 
(list 4480.561 872.2397) 
(list 4480.561 872.25) 
(list 4481.122 872.25)))
(apply 'command (append '("pline") coords '("c")))
(setq tap14 (ssadd (entlast) tap14))
(command "_mirror" (entlast) "" "4480,900" "4480,901" "No")
(setq tap14 (ssadd (entlast) tap14))
(command "_block" "blktap14" "4480,900" tap14 "")
(command "_insert" "blktap14" "4480,900" "1" "1" "0")
(command "_insert" "blktap14" "4480,900" "1" "1" "180")
(setq uc14 nil)
(setq uc14 (ssadd))
(setq coords (list 
(list 0 -0.185) 
(list 0.125 -0.185) 
(list 0.125 -0.17472) 
(list 0.125 -0.16444) 
(list 0.125 -0.15417) 
(list 0.125 -0.14389) 
(list 0.125 -0.13361) 
(list 0.125 -0.12333) 
(list 0.125 -0.11306) 
(list 0.125 -0.10278) 
(list 0.125 -0.0925) 
(list 0.125 -0.082222) 
(list 0.125 -0.071944) 
(list 0.125 -0.061667) 
(list 0.125 -0.051389) 
(list 0.125 -0.041111) 
(list 0.125 -0.030833) 
(list 0.125 -0.020556) 
(list 0.125 -0.010278) 
(list 0.125 0) 
(list 0.125 0.010278) 
(list 0.125 0.020556) 
(list 0.125 0.030833) 
(list 0.125 0.041111) 
(list 0.125 0.051389) 
(list 0.125 0.061667) 
(list 0.125 0.071944) 
(list 0.125 0.082222) 
(list 0.125 0.0925) 
(list 0.125 0.10278) 
(list 0.125 0.11306) 
(list 0.125 0.12333) 
(list 0.125 0.13361) 
(list 0.125 0.14389) 
(list 0.125 0.15417) 
(list 0.125 0.16444) 
(list 0.125 0.17472) 
(list 0.125 0.185) 
(list 0 0.185)))
(apply 'command (append '("pline") coords '("c")))
(setq uc14 (ssadd (entlast) uc14))
(setq coords (list 
(list 1.122 -0.185) 
(list 0.561 -0.185) 
(list 0.559 -0.17472) 
(list 0.55304 -0.16444) 
(list 0.54331 -0.15417) 
(list 0.53012 -0.14389) 
(list 0.51385 -0.13361) 
(list 0.495 -0.12333) 
(list 0.47415 -0.11306) 
(list 0.45192 -0.10278) 
(list 0.429 -0.0925) 
(list 0.40608 -0.082222) 
(list 0.38385 -0.071944) 
(list 0.363 -0.061667) 
(list 0.34415 -0.051389) 
(list 0.32788 -0.041111) 
(list 0.31468 -0.030833) 
(list 0.30496 -0.020556) 
(list 0.29901 -0.010278) 
(list 0.297 0) 
(list 0.29901 0.010278) 
(list 0.30496 0.020556) 
(list 0.31468 0.030833) 
(list 0.32788 0.041111) 
(list 0.34415 0.051389) 
(list 0.363 0.061667) 
(list 0.38385 0.071944) 
(list 0.40608 0.082222) 
(list 0.429 0.0925) 
(list 0.45192 0.10278) 
(list 0.47415 0.11306) 
(list 0.495 0.12333) 
(list 0.51385 0.13361) 
(list 0.53012 0.14389) 
(list 0.54331 0.15417) 
(list 0.55304 0.16444) 
(list 0.559 0.17472) 
(list 0.561 0.185) 
(list 1.122 0.185)))
(apply 'command (append '("pline") coords '("c")))
(setq uc14 (ssadd (entlast) uc14))
(command "_block" "blkuc14" "0,0.185" uc14 "")
(command "_insert" "blkuc14" "4480,872.62" "1" "1" "0")
(command "_insert" "blkuc14" "4480,872.25" "1" "1" "180")
(command "_insert" "blkuc14" "4480,872.99" "1" "1" "0")
(command "_insert" "blkuc14" "4480,872.62" "1" "1" "180")
(command "_insert" "blkuc14" "4480,873.36" "1" "1" "0")
(command "_insert" "blkuc14" "4480,872.99" "1" "1" "180")
(command "_insert" "blkuc14" "4480,873.73" "1" "1" "0")
(command "_insert" "blkuc14" "4480,873.36" "1" "1" "180")
(command "_insert" "blkuc14" "4480,874.1" "1" "1" "0")
(command "_insert" "blkuc14" "4480,873.73" "1" "1" "180")
(command "_insert" "blkuc14" "4480,874.47" "1" "1" "0")
(command "_insert" "blkuc14" "4480,874.1" "1" "1" "180")
(command "_insert" "blkuc14" "4480,874.84" "1" "1" "0")
(command "_insert" "blkuc14" "4480,874.47" "1" "1" "180")
(command "_insert" "blkuc14" "4480,875.21" "1" "1" "0")
(command "_insert" "blkuc14" "4480,874.84" "1" "1" "180")
(command "_insert" "blkuc14" "4480,875.58" "1" "1" "0")
(command "_insert" "blkuc14" "4480,875.21" "1" "1" "180")
(command "_insert" "blkuc14" "4480,875.95" "1" "1" "0")
(command "_insert" "blkuc14" "4480,875.58" "1" "1" "180")
(command "_insert" "blkuc14" "4480,876.32" "1" "1" "0")
(command "_insert" "blkuc14" "4480,875.95" "1" "1" "180")
(command "_insert" "blkuc14" "4480,876.69" "1" "1" "0")
(command "_insert" "blkuc14" "4480,876.32" "1" "1" "180")
(command "_insert" "blkuc14" "4480,877.06" "1" "1" "0")
(command "_insert" "blkuc14" "4480,876.69" "1" "1" "180")
(command "_insert" "blkuc14" "4480,877.43" "1" "1" "0")
(command "_insert" "blkuc14" "4480,877.06" "1" "1" "180")
(command "_insert" "blkuc14" "4480,877.8" "1" "1" "0")
(command "_insert" "blkuc14" "4480,877.43" "1" "1" "180")
(command "_insert" "blkuc14" "4480,878.17" "1" "1" "0")
(command "_insert" "blkuc14" "4480,877.8" "1" "1" "180")
(command "_insert" "blkuc14" "4480,878.54" "1" "1" "0")
(command "_insert" "blkuc14" "4480,878.17" "1" "1" "180")
(command "_insert" "blkuc14" "4480,878.91" "1" "1" "0")
(command "_insert" "blkuc14" "4480,878.54" "1" "1" "180")
(command "_insert" "blkuc14" "4480,879.28" "1" "1" "0")
(command "_insert" "blkuc14" "4480,878.91" "1" "1" "180")
(command "_insert" "blkuc14" "4480,879.65" "1" "1" "0")
(command "_insert" "blkuc14" "4480,879.28" "1" "1" "180")
(command "_insert" "blkuc14" "4480,880.02" "1" "1" "0")
(command "_insert" "blkuc14" "4480,879.65" "1" "1" "180")
(command "_insert" "blkuc14" "4480,880.39" "1" "1" "0")
(command "_insert" "blkuc14" "4480,880.02" "1" "1" "180")
(command "_insert" "blkuc14" "4480,880.76" "1" "1" "0")
(command "_insert" "blkuc14" "4480,880.39" "1" "1" "180")
(command "_insert" "blkuc14" "4480,881.13" "1" "1" "0")
(command "_insert" "blkuc14" "4480,880.76" "1" "1" "180")
(command "_insert" "blkuc14" "4480,881.5" "1" "1" "0")
(command "_insert" "blkuc14" "4480,881.13" "1" "1" "180")
(command "_insert" "blkuc14" "4480,881.87" "1" "1" "0")
(command "_insert" "blkuc14" "4480,881.5" "1" "1" "180")
(command "_insert" "blkuc14" "4480,882.24" "1" "1" "0")
(command "_insert" "blkuc14" "4480,881.87" "1" "1" "180")
(command "_insert" "blkuc14" "4480,882.61" "1" "1" "0")
(command "_insert" "blkuc14" "4480,882.24" "1" "1" "180")
(command "_insert" "blkuc14" "4480,882.98" "1" "1" "0")
(command "_insert" "blkuc14" "4480,882.61" "1" "1" "180")
(command "_insert" "blkuc14" "4480,883.35" "1" "1" "0")
(command "_insert" "blkuc14" "4480,882.98" "1" "1" "180")
(command "_insert" "blkuc14" "4480,883.72" "1" "1" "0")
(command "_insert" "blkuc14" "4480,883.35" "1" "1" "180")
(command "_insert" "blkuc14" "4480,884.09" "1" "1" "0")
(command "_insert" "blkuc14" "4480,883.72" "1" "1" "180")
(command "_insert" "blkuc14" "4480,884.46" "1" "1" "0")
(command "_insert" "blkuc14" "4480,884.09" "1" "1" "180")
(command "_insert" "blkuc14" "4480,884.83" "1" "1" "0")
(command "_insert" "blkuc14" "4480,884.46" "1" "1" "180")
(command "_insert" "blkuc14" "4480,885.2" "1" "1" "0")
(command "_insert" "blkuc14" "4480,884.83" "1" "1" "180")
(command "_insert" "blkuc14" "4480,885.57" "1" "1" "0")
(command "_insert" "blkuc14" "4480,885.2" "1" "1" "180")
(command "_insert" "blkuc14" "4480,885.94" "1" "1" "0")
(command "_insert" "blkuc14" "4480,885.57" "1" "1" "180")
(command "_insert" "blkuc14" "4480,886.31" "1" "1" "0")
(command "_insert" "blkuc14" "4480,885.94" "1" "1" "180")
(command "_insert" "blkuc14" "4480,886.68" "1" "1" "0")
(command "_insert" "blkuc14" "4480,886.31" "1" "1" "180")
(command "_insert" "blkuc14" "4480,887.05" "1" "1" "0")
(command "_insert" "blkuc14" "4480,886.68" "1" "1" "180")
(command "_insert" "blkuc14" "4480,887.42" "1" "1" "0")
(command "_insert" "blkuc14" "4480,887.05" "1" "1" "180")
(command "_insert" "blkuc14" "4480,887.79" "1" "1" "0")
(command "_insert" "blkuc14" "4480,887.42" "1" "1" "180")
(command "_insert" "blkuc14" "4480,888.16" "1" "1" "0")
(command "_insert" "blkuc14" "4480,887.79" "1" "1" "180")
(command "_insert" "blkuc14" "4480,888.53" "1" "1" "0")
(command "_insert" "blkuc14" "4480,888.16" "1" "1" "180")
(command "_insert" "blkuc14" "4480,888.9" "1" "1" "0")
(command "_insert" "blkuc14" "4480,888.53" "1" "1" "180")
(command "_insert" "blkuc14" "4480,889.27" "1" "1" "0")
(command "_insert" "blkuc14" "4480,888.9" "1" "1" "180")
(command "_insert" "blkuc14" "4480,889.64" "1" "1" "0")
(command "_insert" "blkuc14" "4480,889.27" "1" "1" "180")
(command "_insert" "blkuc14" "4480,890.01" "1" "1" "0")
(command "_insert" "blkuc14" "4480,889.64" "1" "1" "180")
(command "_insert" "blkuc14" "4480,890.38" "1" "1" "0")
(command "_insert" "blkuc14" "4480,890.01" "1" "1" "180")
(command "_insert" "blkuc14" "4480,890.75" "1" "1" "0")
(command "_insert" "blkuc14" "4480,890.38" "1" "1" "180")
(command "_insert" "blkuc14" "4480,891.12" "1" "1" "0")
(command "_insert" "blkuc14" "4480,890.75" "1" "1" "180")
(command "_insert" "blkuc14" "4480,891.49" "1" "1" "0")
(command "_insert" "blkuc14" "4480,891.12" "1" "1" "180")
(command "_insert" "blkuc14" "4480,891.86" "1" "1" "0")
(command "_insert" "blkuc14" "4480,891.49" "1" "1" "180")
(command "_insert" "blkuc14" "4480,892.23" "1" "1" "0")
(command "_insert" "blkuc14" "4480,891.86" "1" "1" "180")
(command "_insert" "blkuc14" "4480,892.6" "1" "1" "0")
(command "_insert" "blkuc14" "4480,892.23" "1" "1" "180")
(command "_insert" "blkuc14" "4480,892.97" "1" "1" "0")
(command "_insert" "blkuc14" "4480,892.6" "1" "1" "180")
(command "_insert" "blkuc14" "4480,893.34" "1" "1" "0")
(command "_insert" "blkuc14" "4480,892.97" "1" "1" "180")
(command "_insert" "blkuc14" "4480,893.71" "1" "1" "0")
(command "_insert" "blkuc14" "4480,893.34" "1" "1" "180")
(command "_insert" "blkuc14" "4480,894.08" "1" "1" "0")
(command "_insert" "blkuc14" "4480,893.71" "1" "1" "180")
(command "_insert" "blkuc14" "4480,894.45" "1" "1" "0")
(command "_insert" "blkuc14" "4480,894.08" "1" "1" "180")
(command "_insert" "blkuc14" "4480,894.82" "1" "1" "0")
(command "_insert" "blkuc14" "4480,894.45" "1" "1" "180")
(command "_insert" "blkuc14" "4480,895.19" "1" "1" "0")
(command "_insert" "blkuc14" "4480,894.82" "1" "1" "180")
(command "_insert" "blkuc14" "4480,895.56" "1" "1" "0")
(command "_insert" "blkuc14" "4480,895.19" "1" "1" "180")
(command "_insert" "blkuc14" "4480,895.93" "1" "1" "0")
(command "_insert" "blkuc14" "4480,895.56" "1" "1" "180")
(command "_insert" "blkuc14" "4480,896.3" "1" "1" "0")
(command "_insert" "blkuc14" "4480,895.93" "1" "1" "180")
(command "_insert" "blkuc14" "4480,896.67" "1" "1" "0")
(command "_insert" "blkuc14" "4480,896.3" "1" "1" "180")
(command "_insert" "blkuc14" "4480,897.04" "1" "1" "0")
(command "_insert" "blkuc14" "4480,896.67" "1" "1" "180")
(command "_insert" "blkuc14" "4480,897.41" "1" "1" "0")
(command "_insert" "blkuc14" "4480,897.04" "1" "1" "180")
(command "_insert" "blkuc14" "4480,897.78" "1" "1" "0")
(command "_insert" "blkuc14" "4480,897.41" "1" "1" "180")
(command "_insert" "blkuc14" "4480,898.15" "1" "1" "0")
(command "_insert" "blkuc14" "4480,897.78" "1" "1" "180")
(command "_insert" "blkuc14" "4480,898.52" "1" "1" "0")
(command "_insert" "blkuc14" "4480,898.15" "1" "1" "180")
(command "_insert" "blkuc14" "4480,898.89" "1" "1" "0")
(command "_insert" "blkuc14" "4480,898.52" "1" "1" "180")
(command "_insert" "blkuc14" "4480,899.26" "1" "1" "0")
(command "_insert" "blkuc14" "4480,898.89" "1" "1" "180")
(command "_insert" "blkuc14" "4480,899.63" "1" "1" "0")
(command "_insert" "blkuc14" "4480,899.26" "1" "1" "180")
(command "_insert" "blkuc14" "4480,900" "1" "1" "0")
(command "_insert" "blkuc14" "4480,899.63" "1" "1" "180")
(command "_insert" "blkuc14" "4480,900.37" "1" "1" "0")
(command "_insert" "blkuc14" "4480,900" "1" "1" "180")
(command "_insert" "blkuc14" "4480,900.74" "1" "1" "0")
(command "_insert" "blkuc14" "4480,900.37" "1" "1" "180")
(command "_insert" "blkuc14" "4480,901.11" "1" "1" "0")
(command "_insert" "blkuc14" "4480,900.74" "1" "1" "180")
(command "_insert" "blkuc14" "4480,901.48" "1" "1" "0")
(command "_insert" "blkuc14" "4480,901.11" "1" "1" "180")
(command "_insert" "blkuc14" "4480,901.85" "1" "1" "0")
(command "_insert" "blkuc14" "4480,901.48" "1" "1" "180")
(command "_insert" "blkuc14" "4480,902.22" "1" "1" "0")
(command "_insert" "blkuc14" "4480,901.85" "1" "1" "180")
(command "_insert" "blkuc14" "4480,902.59" "1" "1" "0")
(command "_insert" "blkuc14" "4480,902.22" "1" "1" "180")
(command "_insert" "blkuc14" "4480,902.96" "1" "1" "0")
(command "_insert" "blkuc14" "4480,902.59" "1" "1" "180")
(command "_insert" "blkuc14" "4480,903.33" "1" "1" "0")
(command "_insert" "blkuc14" "4480,902.96" "1" "1" "180")
(command "_insert" "blkuc14" "4480,903.7" "1" "1" "0")
(command "_insert" "blkuc14" "4480,903.33" "1" "1" "180")
(command "_insert" "blkuc14" "4480,904.07" "1" "1" "0")
(command "_insert" "blkuc14" "4480,903.7" "1" "1" "180")
(command "_insert" "blkuc14" "4480,904.44" "1" "1" "0")
(command "_insert" "blkuc14" "4480,904.07" "1" "1" "180")
(command "_insert" "blkuc14" "4480,904.81" "1" "1" "0")
(command "_insert" "blkuc14" "4480,904.44" "1" "1" "180")
(command "_insert" "blkuc14" "4480,905.18" "1" "1" "0")
(command "_insert" "blkuc14" "4480,904.81" "1" "1" "180")
(command "_insert" "blkuc14" "4480,905.55" "1" "1" "0")
(command "_insert" "blkuc14" "4480,905.18" "1" "1" "180")
(command "_insert" "blkuc14" "4480,905.92" "1" "1" "0")
(command "_insert" "blkuc14" "4480,905.55" "1" "1" "180")
(command "_insert" "blkuc14" "4480,906.29" "1" "1" "0")
(command "_insert" "blkuc14" "4480,905.92" "1" "1" "180")
(command "_insert" "blkuc14" "4480,906.66" "1" "1" "0")
(command "_insert" "blkuc14" "4480,906.29" "1" "1" "180")
(command "_insert" "blkuc14" "4480,907.03" "1" "1" "0")
(command "_insert" "blkuc14" "4480,906.66" "1" "1" "180")
(command "_insert" "blkuc14" "4480,907.4" "1" "1" "0")
(command "_insert" "blkuc14" "4480,907.03" "1" "1" "180")
(command "_insert" "blkuc14" "4480,907.77" "1" "1" "0")
(command "_insert" "blkuc14" "4480,907.4" "1" "1" "180")
(command "_insert" "blkuc14" "4480,908.14" "1" "1" "0")
(command "_insert" "blkuc14" "4480,907.77" "1" "1" "180")
(command "_insert" "blkuc14" "4480,908.51" "1" "1" "0")
(command "_insert" "blkuc14" "4480,908.14" "1" "1" "180")
(command "_insert" "blkuc14" "4480,908.88" "1" "1" "0")
(command "_insert" "blkuc14" "4480,908.51" "1" "1" "180")
(command "_insert" "blkuc14" "4480,909.25" "1" "1" "0")
(command "_insert" "blkuc14" "4480,908.88" "1" "1" "180")
(command "_insert" "blkuc14" "4480,909.62" "1" "1" "0")
(command "_insert" "blkuc14" "4480,909.25" "1" "1" "180")
(command "_insert" "blkuc14" "4480,909.99" "1" "1" "0")
(command "_insert" "blkuc14" "4480,909.62" "1" "1" "180")
(command "_insert" "blkuc14" "4480,910.36" "1" "1" "0")
(command "_insert" "blkuc14" "4480,909.99" "1" "1" "180")
(command "_insert" "blkuc14" "4480,910.73" "1" "1" "0")
(command "_insert" "blkuc14" "4480,910.36" "1" "1" "180")
(command "_insert" "blkuc14" "4480,911.1" "1" "1" "0")
(command "_insert" "blkuc14" "4480,910.73" "1" "1" "180")
(command "_insert" "blkuc14" "4480,911.47" "1" "1" "0")
(command "_insert" "blkuc14" "4480,911.1" "1" "1" "180")
(command "_insert" "blkuc14" "4480,911.84" "1" "1" "0")
(command "_insert" "blkuc14" "4480,911.47" "1" "1" "180")
(command "_insert" "blkuc14" "4480,912.21" "1" "1" "0")
(command "_insert" "blkuc14" "4480,911.84" "1" "1" "180")
(command "_insert" "blkuc14" "4480,912.58" "1" "1" "0")
(command "_insert" "blkuc14" "4480,912.21" "1" "1" "180")
(command "_insert" "blkuc14" "4480,912.95" "1" "1" "0")
(command "_insert" "blkuc14" "4480,912.58" "1" "1" "180")
(command "_insert" "blkuc14" "4480,913.32" "1" "1" "0")
(command "_insert" "blkuc14" "4480,912.95" "1" "1" "180")
(command "_insert" "blkuc14" "4480,913.69" "1" "1" "0")
(command "_insert" "blkuc14" "4480,913.32" "1" "1" "180")
(command "_insert" "blkuc14" "4480,914.06" "1" "1" "0")
(command "_insert" "blkuc14" "4480,913.69" "1" "1" "180")
(command "_insert" "blkuc14" "4480,914.43" "1" "1" "0")
(command "_insert" "blkuc14" "4480,914.06" "1" "1" "180")
(command "_insert" "blkuc14" "4480,914.8" "1" "1" "0")
(command "_insert" "blkuc14" "4480,914.43" "1" "1" "180")
(command "_insert" "blkuc14" "4480,915.17" "1" "1" "0")
(command "_insert" "blkuc14" "4480,914.8" "1" "1" "180")
(command "_insert" "blkuc14" "4480,915.54" "1" "1" "0")
(command "_insert" "blkuc14" "4480,915.17" "1" "1" "180")
(command "_insert" "blkuc14" "4480,915.91" "1" "1" "0")
(command "_insert" "blkuc14" "4480,915.54" "1" "1" "180")
(command "_insert" "blkuc14" "4480,916.28" "1" "1" "0")
(command "_insert" "blkuc14" "4480,915.91" "1" "1" "180")
(command "_insert" "blkuc14" "4480,916.65" "1" "1" "0")
(command "_insert" "blkuc14" "4480,916.28" "1" "1" "180")
(command "_insert" "blkuc14" "4480,917.02" "1" "1" "0")
(command "_insert" "blkuc14" "4480,916.65" "1" "1" "180")
(command "_insert" "blkuc14" "4480,917.39" "1" "1" "0")
(command "_insert" "blkuc14" "4480,917.02" "1" "1" "180")
(command "_insert" "blkuc14" "4480,917.76" "1" "1" "0")
(command "_insert" "blkuc14" "4480,917.39" "1" "1" "180")
(command "_insert" "blkuc14" "4480,918.13" "1" "1" "0")
(command "_insert" "blkuc14" "4480,917.76" "1" "1" "180")
(command "_insert" "blkuc14" "4480,918.5" "1" "1" "0")
(command "_insert" "blkuc14" "4480,918.13" "1" "1" "180")
(command "_insert" "blkuc14" "4480,918.87" "1" "1" "0")
(command "_insert" "blkuc14" "4480,918.5" "1" "1" "180")
(command "_insert" "blkuc14" "4480,919.24" "1" "1" "0")
(command "_insert" "blkuc14" "4480,918.87" "1" "1" "180")
(command "_insert" "blkuc14" "4480,919.61" "1" "1" "0")
(command "_insert" "blkuc14" "4480,919.24" "1" "1" "180")
(command "_insert" "blkuc14" "4480,919.98" "1" "1" "0")
(command "_insert" "blkuc14" "4480,919.61" "1" "1" "180")
(command "_insert" "blkuc14" "4480,920.35" "1" "1" "0")
(command "_insert" "blkuc14" "4480,919.98" "1" "1" "180")
(command "_insert" "blkuc14" "4480,920.72" "1" "1" "0")
(command "_insert" "blkuc14" "4480,920.35" "1" "1" "180")
(command "_insert" "blkuc14" "4480,921.09" "1" "1" "0")
(command "_insert" "blkuc14" "4480,920.72" "1" "1" "180")
(command "_insert" "blkuc14" "4480,921.46" "1" "1" "0")
(command "_insert" "blkuc14" "4480,921.09" "1" "1" "180")
(command "_insert" "blkuc14" "4480,921.83" "1" "1" "0")
(command "_insert" "blkuc14" "4480,921.46" "1" "1" "180")
(command "_insert" "blkuc14" "4480,922.2" "1" "1" "0")
(command "_insert" "blkuc14" "4480,921.83" "1" "1" "180")
(command "_insert" "blkuc14" "4480,922.57" "1" "1" "0")
(command "_insert" "blkuc14" "4480,922.2" "1" "1" "180")
(command "_insert" "blkuc14" "4480,922.94" "1" "1" "0")
(command "_insert" "blkuc14" "4480,922.57" "1" "1" "180")
(command "_insert" "blkuc14" "4480,923.31" "1" "1" "0")
(command "_insert" "blkuc14" "4480,922.94" "1" "1" "180")
(command "_insert" "blkuc14" "4480,923.68" "1" "1" "0")
(command "_insert" "blkuc14" "4480,923.31" "1" "1" "180")
(command "_insert" "blkuc14" "4480,924.05" "1" "1" "0")
(command "_insert" "blkuc14" "4480,923.68" "1" "1" "180")
(command "_insert" "blkuc14" "4480,924.42" "1" "1" "0")
(command "_insert" "blkuc14" "4480,924.05" "1" "1" "180")
(command "_insert" "blkuc14" "4480,924.79" "1" "1" "0")
(command "_insert" "blkuc14" "4480,924.42" "1" "1" "180")
(command "_insert" "blkuc14" "4480,925.16" "1" "1" "0")
(command "_insert" "blkuc14" "4480,924.79" "1" "1" "180")
(command "_insert" "blkuc14" "4480,925.53" "1" "1" "0")
(command "_insert" "blkuc14" "4480,925.16" "1" "1" "180")
(command "_insert" "blkuc14" "4480,925.9" "1" "1" "0")
(command "_insert" "blkuc14" "4480,925.53" "1" "1" "180")
(command "_insert" "blkuc14" "4480,926.27" "1" "1" "0")
(command "_insert" "blkuc14" "4480,925.9" "1" "1" "180")
(command "_insert" "blkuc14" "4480,926.64" "1" "1" "0")
(command "_insert" "blkuc14" "4480,926.27" "1" "1" "180")
(command "_insert" "blkuc14" "4480,927.01" "1" "1" "0")
(command "_insert" "blkuc14" "4480,926.64" "1" "1" "180")
(command "_insert" "blkuc14" "4480,927.38" "1" "1" "0")
(command "_insert" "blkuc14" "4480,927.01" "1" "1" "180")
(command "_insert" "blkuc14" "4480,927.75" "1" "1" "0")
(command "_insert" "blkuc14" "4480,927.38" "1" "1" "180")
(command "_layer" "set" "phccover" "")
(command "_rectangle" "4478.878,933.3" "4481.122,866.7")
(command "_layer" "set" "nitride" "")
(setq phc14 currobj)
(command "_layer" "set" "cover" "")
(command "_rectangle" "4478.878,836.7" "4481.122,963.3")
(command "_layer" "set" "nitride" "")
(command "_layer" "set" "text" "")
(command "_circle" "4477.928,846.7" "0.075")
(command "_circle" "4477.553,846.7" "0.15")
(command "_circle" "4477.178,846.7" "0.075")
(command "_circle" "4476.803,846.7" "0.15")
(command "_circle" "4477.928,848.7" "0.075")
(command "_circle" "4477.553,848.7" "0.075")
(command "_circle" "4477.178,848.7" "0.15")
(command "_circle" "4476.803,848.7" "0.15")
(command "_circle" "4477.928,850.7" "0.075")
(command "_circle" "4477.553,850.7" "0.15")
(command "_circle" "4477.178,850.7" "0.15")
(command "_circle" "4476.803,850.7" "0.15")
(command "_circle" "4477.928,852.7" "0.075")
(command "_circle" "4477.553,852.7" "0.075")
(command "_circle" "4477.178,852.7" "0.075")
(command "_circle" "4476.803,852.7" "0.075")
(command "_circle" "4476.428,852.7" "0.15")
(command "_circle" "4477.928,854.7" "0.075")
(command "_circle" "4477.553,854.7" "0.15")
(command "_circle" "4477.178,854.7" "0.075")
(command "_circle" "4476.803,854.7" "0.075")
(command "_circle" "4476.428,854.7" "0.15")
(command "_circle" "4477.928,856.7" "0.075")
(command "_circle" "4477.553,856.7" "0.075")
(command "_circle" "4477.178,856.7" "0.15")
(command "_circle" "4476.803,856.7" "0.075")
(command "_circle" "4476.428,856.7" "0.15")
(command "_circle" "4477.928,858.7" "0.075")
(command "_circle" "4477.553,858.7" "0.15")
(command "_circle" "4477.178,858.7" "0.15")
(command "_circle" "4476.803,858.7" "0.075")
(command "_circle" "4476.428,858.7" "0.15")
(command "_circle" "4477.928,860.7" "0.075")
(command "_circle" "4477.553,860.7" "0.075")
(command "_circle" "4477.178,860.7" "0.075")
(command "_circle" "4476.803,860.7" "0.15")
(command "_circle" "4476.428,860.7" "0.15")
(command "_circle" "4477.928,862.7" "0.075")
(command "_circle" "4477.553,862.7" "0.15")
(command "_circle" "4477.178,862.7" "0.075")
(command "_circle" "4476.803,862.7" "0.15")
(command "_circle" "4476.428,862.7" "0.15")
(command "_circle" "4477.928,864.7" "0.075")
(command "_circle" "4477.553,864.7" "0.075")
(command "_circle" "4477.178,864.7" "0.15")
(command "_circle" "4476.803,864.7" "0.15")
(command "_circle" "4476.428,864.7" "0.15")
(command "_circle" "4477.928,866.7" "0.075")
(command "_circle" "4477.553,866.7" "0.15")
(command "_circle" "4477.178,866.7" "0.15")
(command "_circle" "4476.803,866.7" "0.15")
(command "_circle" "4476.428,866.7" "0.15")
(command "_circle" "4477.928,868.7" "0.075")
(command "_circle" "4477.553,868.7" "0.075")
(command "_circle" "4477.178,868.7" "0.075")
(command "_circle" "4476.803,868.7" "0.075")
(command "_circle" "4476.428,868.7" "0.075")
(command "_circle" "4476.053,868.7" "0.15")
(command "_circle" "4477.928,870.7" "0.075")
(command "_circle" "4477.553,870.7" "0.15")
(command "_circle" "4477.178,870.7" "0.075")
(command "_circle" "4476.803,870.7" "0.075")
(command "_circle" "4476.428,870.7" "0.075")
(command "_circle" "4476.053,870.7" "0.15")
(command "_circle" "4477.928,872.7" "0.075")
(command "_circle" "4477.553,872.7" "0.075")
(command "_circle" "4477.178,872.7" "0.15")
(command "_circle" "4476.803,872.7" "0.075")
(command "_circle" "4476.428,872.7" "0.075")
(command "_circle" "4476.053,872.7" "0.15")
(command "_circle" "4477.928,874.7" "0.075")
(command "_circle" "4477.553,874.7" "0.15")
(command "_circle" "4477.178,874.7" "0.15")
(command "_circle" "4476.803,874.7" "0.075")
(command "_circle" "4476.428,874.7" "0.075")
(command "_circle" "4476.053,874.7" "0.15")
(command "_circle" "4477.928,876.7" "0.075")
(command "_circle" "4477.553,876.7" "0.075")
(command "_circle" "4477.178,876.7" "0.075")
(command "_circle" "4476.803,876.7" "0.15")
(command "_circle" "4476.428,876.7" "0.075")
(command "_circle" "4476.053,876.7" "0.15")
(command "_circle" "4477.928,878.7" "0.075")
(command "_circle" "4477.553,878.7" "0.15")
(command "_circle" "4477.178,878.7" "0.075")
(command "_circle" "4476.803,878.7" "0.15")
(command "_circle" "4476.428,878.7" "0.075")
(command "_circle" "4476.053,878.7" "0.15")
(command "_circle" "4477.928,880.7" "0.075")
(command "_circle" "4477.553,880.7" "0.075")
(command "_circle" "4477.178,880.7" "0.15")
(command "_circle" "4476.803,880.7" "0.15")
(command "_circle" "4476.428,880.7" "0.075")
(command "_circle" "4476.053,880.7" "0.15")
(command "_circle" "4477.928,882.7" "0.075")
(command "_circle" "4477.553,882.7" "0.15")
(command "_circle" "4477.178,882.7" "0.15")
(command "_circle" "4476.803,882.7" "0.15")
(command "_circle" "4476.428,882.7" "0.075")
(command "_circle" "4476.053,882.7" "0.15")
(command "_circle" "4477.928,884.7" "0.075")
(command "_circle" "4477.553,884.7" "0.075")
(command "_circle" "4477.178,884.7" "0.075")
(command "_circle" "4476.803,884.7" "0.075")
(command "_circle" "4476.428,884.7" "0.15")
(command "_circle" "4476.053,884.7" "0.15")
(command "_circle" "4477.928,886.7" "0.075")
(command "_circle" "4477.553,886.7" "0.15")
(command "_circle" "4477.178,886.7" "0.075")
(command "_circle" "4476.803,886.7" "0.075")
(command "_circle" "4476.428,886.7" "0.15")
(command "_circle" "4476.053,886.7" "0.15")
(command "_circle" "4477.928,888.7" "0.075")
(command "_circle" "4477.553,888.7" "0.075")
(command "_circle" "4477.178,888.7" "0.15")
(command "_circle" "4476.803,888.7" "0.075")
(command "_circle" "4476.428,888.7" "0.15")
(command "_circle" "4476.053,888.7" "0.15")
(command "_circle" "4477.928,890.7" "0.075")
(command "_circle" "4477.553,890.7" "0.15")
(command "_circle" "4477.178,890.7" "0.15")
(command "_circle" "4476.803,890.7" "0.075")
(command "_circle" "4476.428,890.7" "0.15")
(command "_circle" "4476.053,890.7" "0.15")
(command "_circle" "4477.928,892.7" "0.075")
(command "_circle" "4477.553,892.7" "0.075")
(command "_circle" "4477.178,892.7" "0.075")
(command "_circle" "4476.803,892.7" "0.15")
(command "_circle" "4476.428,892.7" "0.15")
(command "_circle" "4476.053,892.7" "0.15")
(command "_circle" "4477.928,894.7" "0.075")
(command "_circle" "4477.553,894.7" "0.15")
(command "_circle" "4477.178,894.7" "0.075")
(command "_circle" "4476.803,894.7" "0.15")
(command "_circle" "4476.428,894.7" "0.15")
(command "_circle" "4476.053,894.7" "0.15")
(command "_circle" "4477.928,896.7" "0.075")
(command "_circle" "4477.553,896.7" "0.075")
(command "_circle" "4477.178,896.7" "0.15")
(command "_circle" "4476.803,896.7" "0.15")
(command "_circle" "4476.428,896.7" "0.15")
(command "_circle" "4476.053,896.7" "0.15")
(command "_circle" "4477.928,898.7" "0.075")
(command "_circle" "4477.553,898.7" "0.15")
(command "_circle" "4477.178,898.7" "0.15")
(command "_circle" "4476.803,898.7" "0.15")
(command "_circle" "4476.428,898.7" "0.15")
(command "_circle" "4476.053,898.7" "0.15")
(command "_circle" "4477.928,900.7" "0.075")
(command "_circle" "4477.553,900.7" "0.075")
(command "_circle" "4477.178,900.7" "0.075")
(command "_circle" "4476.803,900.7" "0.075")
(command "_circle" "4476.428,900.7" "0.075")
(command "_circle" "4476.053,900.7" "0.075")
(command "_circle" "4475.678,900.7" "0.15")
(command "_circle" "4477.928,902.7" "0.075")
(command "_circle" "4477.553,902.7" "0.15")
(command "_circle" "4477.178,902.7" "0.075")
(command "_circle" "4476.803,902.7" "0.075")
(command "_circle" "4476.428,902.7" "0.075")
(command "_circle" "4476.053,902.7" "0.075")
(command "_circle" "4475.678,902.7" "0.15")
(command "_circle" "4477.928,904.7" "0.075")
(command "_circle" "4477.553,904.7" "0.075")
(command "_circle" "4477.178,904.7" "0.15")
(command "_circle" "4476.803,904.7" "0.075")
(command "_circle" "4476.428,904.7" "0.075")
(command "_circle" "4476.053,904.7" "0.075")
(command "_circle" "4475.678,904.7" "0.15")
(command "_circle" "4477.928,906.7" "0.075")
(command "_circle" "4477.553,906.7" "0.15")
(command "_circle" "4477.178,906.7" "0.15")
(command "_circle" "4476.803,906.7" "0.075")
(command "_circle" "4476.428,906.7" "0.075")
(command "_circle" "4476.053,906.7" "0.075")
(command "_circle" "4475.678,906.7" "0.15")
(command "_circle" "4477.928,908.7" "0.075")
(command "_circle" "4477.553,908.7" "0.075")
(command "_circle" "4477.178,908.7" "0.075")
(command "_circle" "4476.803,908.7" "0.15")
(command "_circle" "4476.428,908.7" "0.075")
(command "_circle" "4476.053,908.7" "0.075")
(command "_circle" "4475.678,908.7" "0.15")
(command "_circle" "4477.928,910.7" "0.075")
(command "_circle" "4477.553,910.7" "0.15")
(command "_circle" "4477.178,910.7" "0.075")
(command "_circle" "4476.803,910.7" "0.15")
(command "_circle" "4476.428,910.7" "0.075")
(command "_circle" "4476.053,910.7" "0.075")
(command "_circle" "4475.678,910.7" "0.15")
(command "_circle" "4477.928,912.7" "0.075")
(command "_circle" "4477.553,912.7" "0.075")
(command "_circle" "4477.178,912.7" "0.15")
(command "_circle" "4476.803,912.7" "0.15")
(command "_circle" "4476.428,912.7" "0.075")
(command "_circle" "4476.053,912.7" "0.075")
(command "_circle" "4475.678,912.7" "0.15")
(command "_circle" "4477.928,914.7" "0.075")
(command "_circle" "4477.553,914.7" "0.15")
(command "_circle" "4477.178,914.7" "0.15")
(command "_circle" "4476.803,914.7" "0.15")
(command "_circle" "4476.428,914.7" "0.075")
(command "_circle" "4476.053,914.7" "0.075")
(command "_circle" "4475.678,914.7" "0.15")
(command "_circle" "4477.928,916.7" "0.075")
(command "_circle" "4477.553,916.7" "0.075")
(command "_circle" "4477.178,916.7" "0.075")
(command "_circle" "4476.803,916.7" "0.075")
(command "_circle" "4476.428,916.7" "0.15")
(command "_circle" "4476.053,916.7" "0.075")
(command "_circle" "4475.678,916.7" "0.15")
(command "_circle" "4477.928,918.7" "0.075")
(command "_circle" "4477.553,918.7" "0.15")
(command "_circle" "4477.178,918.7" "0.075")
(command "_circle" "4476.803,918.7" "0.075")
(command "_circle" "4476.428,918.7" "0.15")
(command "_circle" "4476.053,918.7" "0.075")
(command "_circle" "4475.678,918.7" "0.15")
(command "_circle" "4477.928,920.7" "0.075")
(command "_circle" "4477.553,920.7" "0.075")
(command "_circle" "4477.178,920.7" "0.15")
(command "_circle" "4476.803,920.7" "0.075")
(command "_circle" "4476.428,920.7" "0.15")
(command "_circle" "4476.053,920.7" "0.075")
(command "_circle" "4475.678,920.7" "0.15")
(command "_circle" "4477.928,922.7" "0.075")
(command "_circle" "4477.553,922.7" "0.15")
(command "_circle" "4477.178,922.7" "0.15")
(command "_circle" "4476.803,922.7" "0.075")
(command "_circle" "4476.428,922.7" "0.15")
(command "_circle" "4476.053,922.7" "0.075")
(command "_circle" "4475.678,922.7" "0.15")
(command "_circle" "4477.928,924.7" "0.075")
(command "_circle" "4477.553,924.7" "0.075")
(command "_circle" "4477.178,924.7" "0.075")
(command "_circle" "4476.803,924.7" "0.15")
(command "_circle" "4476.428,924.7" "0.15")
(command "_circle" "4476.053,924.7" "0.075")
(command "_circle" "4475.678,924.7" "0.15")
(command "_circle" "4477.928,926.7" "0.075")
(command "_circle" "4477.553,926.7" "0.15")
(command "_circle" "4477.178,926.7" "0.075")
(command "_circle" "4476.803,926.7" "0.15")
(command "_circle" "4476.428,926.7" "0.15")
(command "_circle" "4476.053,926.7" "0.075")
(command "_circle" "4475.678,926.7" "0.15")
(command "_circle" "4477.928,928.7" "0.075")
(command "_circle" "4477.553,928.7" "0.075")
(command "_circle" "4477.178,928.7" "0.15")
(command "_circle" "4476.803,928.7" "0.15")
(command "_circle" "4476.428,928.7" "0.15")
(command "_circle" "4476.053,928.7" "0.075")
(command "_circle" "4475.678,928.7" "0.15")
(command "_circle" "4477.928,930.7" "0.075")
(command "_circle" "4477.553,930.7" "0.15")
(command "_circle" "4477.178,930.7" "0.15")
(command "_circle" "4476.803,930.7" "0.15")
(command "_circle" "4476.428,930.7" "0.15")
(command "_circle" "4476.053,930.7" "0.075")
(command "_circle" "4475.678,930.7" "0.15")
(command "_circle" "4477.928,932.7" "0.075")
(command "_circle" "4477.553,932.7" "0.075")
(command "_circle" "4477.178,932.7" "0.075")
(command "_circle" "4476.803,932.7" "0.075")
(command "_circle" "4476.428,932.7" "0.075")
(command "_circle" "4476.053,932.7" "0.15")
(command "_circle" "4475.678,932.7" "0.15")
(command "_circle" "4477.928,934.7" "0.075")
(command "_circle" "4477.553,934.7" "0.15")
(command "_circle" "4477.178,934.7" "0.075")
(command "_circle" "4476.803,934.7" "0.075")
(command "_circle" "4476.428,934.7" "0.075")
(command "_circle" "4476.053,934.7" "0.15")
(command "_circle" "4475.678,934.7" "0.15")
(command "_circle" "4477.928,936.7" "0.075")
(command "_circle" "4477.553,936.7" "0.075")
(command "_circle" "4477.178,936.7" "0.15")
(command "_circle" "4476.803,936.7" "0.075")
(command "_circle" "4476.428,936.7" "0.075")
(command "_circle" "4476.053,936.7" "0.15")
(command "_circle" "4475.678,936.7" "0.15")
(command "_circle" "4477.928,938.7" "0.075")
(command "_circle" "4477.553,938.7" "0.15")
(command "_circle" "4477.178,938.7" "0.15")
(command "_circle" "4476.803,938.7" "0.075")
(command "_circle" "4476.428,938.7" "0.075")
(command "_circle" "4476.053,938.7" "0.15")
(command "_circle" "4475.678,938.7" "0.15")
(command "_circle" "4477.928,940.7" "0.075")
(command "_circle" "4477.553,940.7" "0.075")
(command "_circle" "4477.178,940.7" "0.075")
(command "_circle" "4476.803,940.7" "0.15")
(command "_circle" "4476.428,940.7" "0.075")
(command "_circle" "4476.053,940.7" "0.15")
(command "_circle" "4475.678,940.7" "0.15")
(command "_circle" "4477.928,942.7" "0.075")
(command "_circle" "4477.553,942.7" "0.15")
(command "_circle" "4477.178,942.7" "0.075")
(command "_circle" "4476.803,942.7" "0.15")
(command "_circle" "4476.428,942.7" "0.075")
(command "_circle" "4476.053,942.7" "0.15")
(command "_circle" "4475.678,942.7" "0.15")
(command "_circle" "4477.928,944.7" "0.075")
(command "_circle" "4477.553,944.7" "0.075")
(command "_circle" "4477.178,944.7" "0.15")
(command "_circle" "4476.803,944.7" "0.15")
(command "_circle" "4476.428,944.7" "0.075")
(command "_circle" "4476.053,944.7" "0.15")
(command "_circle" "4475.678,944.7" "0.15")
(command "_circle" "4477.928,946.7" "0.075")
(command "_circle" "4477.553,946.7" "0.15")
(command "_circle" "4477.178,946.7" "0.15")
(command "_circle" "4476.803,946.7" "0.15")
(command "_circle" "4476.428,946.7" "0.075")
(command "_circle" "4476.053,946.7" "0.15")
(command "_circle" "4475.678,946.7" "0.15")
(command "_circle" "4477.928,948.7" "0.075")
(command "_circle" "4477.553,948.7" "0.075")
(command "_circle" "4477.178,948.7" "0.075")
(command "_circle" "4476.803,948.7" "0.075")
(command "_circle" "4476.428,948.7" "0.15")
(command "_circle" "4476.053,948.7" "0.15")
(command "_circle" "4475.678,948.7" "0.15")
(command "_circle" "4477.928,950.7" "0.075")
(command "_circle" "4477.553,950.7" "0.15")
(command "_circle" "4477.178,950.7" "0.075")
(command "_circle" "4476.803,950.7" "0.075")
(command "_circle" "4476.428,950.7" "0.15")
(command "_circle" "4476.053,950.7" "0.15")
(command "_circle" "4475.678,950.7" "0.15")
(command "_circle" "4477.928,952.7" "0.075")
(command "_circle" "4477.553,952.7" "0.075")
(command "_circle" "4477.178,952.7" "0.15")
(command "_circle" "4476.803,952.7" "0.075")
(command "_circle" "4476.428,952.7" "0.15")
(command "_circle" "4476.053,952.7" "0.15")
(command "_circle" "4475.678,952.7" "0.15")
(command "_circle" "4477.928,954.7" "0.075")
(command "_circle" "4477.553,954.7" "0.15")
(command "_circle" "4477.178,954.7" "0.15")
(command "_circle" "4476.803,954.7" "0.075")
(command "_circle" "4476.428,954.7" "0.15")
(command "_circle" "4476.053,954.7" "0.15")
(command "_circle" "4475.678,954.7" "0.15")
(command "_circle" "4477.928,956.7" "0.075")
(command "_circle" "4477.553,956.7" "0.075")
(command "_circle" "4477.178,956.7" "0.075")
(command "_circle" "4476.803,956.7" "0.15")
(command "_circle" "4476.428,956.7" "0.15")
(command "_circle" "4476.053,956.7" "0.15")
(command "_circle" "4475.678,956.7" "0.15")
(command "_circle" "4477.928,958.7" "0.075")
(command "_circle" "4477.553,958.7" "0.15")
(command "_circle" "4477.178,958.7" "0.075")
(command "_circle" "4476.803,958.7" "0.15")
(command "_circle" "4476.428,958.7" "0.15")
(command "_circle" "4476.053,958.7" "0.15")
(command "_circle" "4475.678,958.7" "0.15")
(command "_circle" "4477.928,960.7" "0.075")
(command "_circle" "4477.553,960.7" "0.075")
(command "_circle" "4477.178,960.7" "0.15")
(command "_circle" "4476.803,960.7" "0.15")
(command "_circle" "4476.428,960.7" "0.15")
(command "_circle" "4476.053,960.7" "0.15")
(command "_circle" "4475.678,960.7" "0.15")
(command "_circle" "4477.928,962.7" "0.075")
(command "_circle" "4477.553,962.7" "0.15")
(command "_circle" "4477.178,962.7" "0.15")
(command "_circle" "4476.803,962.7" "0.15")
(command "_circle" "4476.428,962.7" "0.15")
(command "_circle" "4476.053,962.7" "0.15")
(command "_circle" "4475.678,962.7" "0.15")
(command "_layer" "set" "nitride" "")
(command "_layer" "set" "text" "")
(command-s "_text" "4466.878,963.3" "2" "-90" "a = 370 nm" )
(sssetfirst nil (ssget "_L"))
(if (not (numberp (vl-string-search "Mac" (getvar "platform")))) (c:txtexp))
(command "_layer" "set" "nitride" "")
(command "_layer" "set" "text" "")
(command-s "_text" "4463.878,963.3" "2" "-90" "gap = 250 nm" )
(sssetfirst nil (ssget "_L"))
(if (not (numberp (vl-string-search "Mac" (getvar "platform")))) (c:txtexp))
(command "_layer" "set" "nitride" "")
(command "_layer" "set" "text" "")
(command-s "_text" "4460.878,963.3" "2" "-90" "amplitude = 132 nm" )
(sssetfirst nil (ssget "_L"))
(if (not (numberp (vl-string-search "Mac" (getvar "platform")))) (c:txtexp))
(command "_layer" "set" "nitride" "")
(command "_layer" "set" "text" "")
(command-s "_text" "4457.878,963.3" "2" "-90" "start width = 280 nm" )
(sssetfirst nil (ssget "_L"))
(if (not (numberp (vl-string-search "Mac" (getvar "platform")))) (c:txtexp))
(command "_layer" "set" "nitride" "")
(command "_layer" "set" "text" "")
(command-s "_text" "4454.878,963.3" "2" "-90" "width = 304 nm" )
(sssetfirst nil (ssget "_L"))
(if (not (numberp (vl-string-search "Mac" (getvar "platform")))) (c:txtexp))
(command "_layer" "set" "nitride" "")
(command "_layer" "set" "text" "")
(command-s "_text" "4451.878,963.3" "2" "-90" "taper: 15" )
(sssetfirst nil (ssget "_L"))
(if (not (numberp (vl-string-search "Mac" (getvar "platform")))) (c:txtexp))
(command "_layer" "set" "nitride" "")
(command "_layer" "set" "text" "")
(command-s "_text" "4448.878,963.3" "2" "-90" "nominal: 150" )
(sssetfirst nil (ssget "_L"))
(if (not (numberp (vl-string-search "Mac" (getvar "platform")))) (c:txtexp))
(command "_layer" "set" "nitride" "")
(command "_layer" "set" "indicators" "")
(setq coords (list 
(list 4400.415 940) 
(list 4400.415 920) 
(list 4380.415 900) 
(list 4400.415 880) 
(list 4400.415 860) 
(list 4400.415 900) 
(list 4400.415 887.0711) 
(list 4387.4861 900) 
(list 4400.415 912.9289) 
(list 4400.415 900)))
(apply 'command (append '("pline") coords '("c")))
(command "._fillet" "radius" "1" "._fillet" "P" (entlast))
(setq coords (list 
(list 4559.585 940) 
(list 4559.585 920) 
(list 4579.585 900) 
(list 4559.585 880) 
(list 4559.585 860) 
(list 4559.585 900) 
(list 4559.585 887.0711) 
(list 4572.5139 900) 
(list 4559.585 912.9289) 
(list 4559.585 900)))
(apply 'command (append '("pline") coords '("c")))
(command "._fillet" "radius" "1" "._fillet" "P" (entlast))
(command "_layer" "set" "holes" "")
(command "_circle" "4398.0629,914.1124" "0.5")
(command "_circle" "4395.7109,911.7603" "0.5")
(command "_circle" "4393.3588,909.4083" "0.5")
(command "_circle" "4391.0067,907.0562" "0.5")
(command "_circle" "4388.6547,904.7041" "0.5")
(command "_circle" "4386.3026,902.3521" "0.5")
(command "_circle" "4383.9505,900" "0.5")
(command "_circle" "4386.3026,897.6479" "0.5")
(command "_circle" "4388.6547,895.2959" "0.5")
(command "_circle" "4391.0067,892.9438" "0.5")
(command "_circle" "4393.3588,890.5917" "0.5")
(command "_circle" "4395.7109,888.2397" "0.5")
(command "_circle" "4398.0629,885.8876" "0.5")
(command "_circle" "4561.9371,914.1124" "0.5")
(command "_circle" "4564.2891,911.7603" "0.5")
(command "_circle" "4566.6412,909.4083" "0.5")
(command "_circle" "4568.9933,907.0562" "0.5")
(command "_circle" "4571.3453,904.7041" "0.5")
(command "_circle" "4573.6974,902.3521" "0.5")
(command "_circle" "4576.0495,900" "0.5")
(command "_circle" "4573.6974,897.6479" "0.5")
(command "_circle" "4571.3453,895.2959" "0.5")
(command "_circle" "4568.9933,892.9438" "0.5")
(command "_circle" "4566.6412,890.5917" "0.5")
(command "_circle" "4564.2891,888.2397" "0.5")
(command "_circle" "4561.9371,885.8876" "0.5")
(command "_layer" "set" "nitride" "")
(command "_block" "blkcoupler14" "4480,900" coupler14 "")
(command "_insert" "blkcoupler14" "4480,900" "1" "1" "0")
(command "_insert" "blkcoupler14" "4480,900" "1" "1" "180")
(command "_block" "blksinglenanobeam14" "4480,900" singlenanobeam14 "")
(command "_insert" "blksinglenanobeam14" "4480,900" "1" "1" "0")
(command "_insert" "blksinglenanobeam14" "4480,900" "1" "1" "180")
(command "_block" "blkanglednodearray14" "4480,900" anglednodearray14 "")
(command "_insert" "blkanglednodearray14" "4480,900" "1" "1" "0")
(command "_insert" "blkanglednodearray14" "4480,900" "1" "1" "180")
(command "_block" "blkcooledsinglenanobeam14" "4480,900" cooledsinglenanobeam14 "")
(command "_insert" "blkcooledsinglenanobeam14" "4480,900" "1" "1" "0")
(command "_insert" "blkcooledsinglenanobeam14" "4480,900" "1" "1" "180")
(command "_block" "blkyjunction14" "4480,900" yjunction14 "")
(command "_insert" "blkyjunction14" "4480,900" "1" "1" "0")
(command "_insert" "blkyjunction14" "4480,900" "1" "1" "180")
; DRAWING BULGING VEE GROOVE
(command "_layer" "set" "vgroove" "")
(setq coords (list 
(list 4405.415 -605) 
(list 4405.415 0) 
(list 4405.415 0) 
(list 4405.415 1800) 
(list 4405.415 1800) 
(list 4405.415 2405) 
(list 4554.585 2405) 
(list 4554.585 1800) 
(list 4554.585 1800) 
(list 4554.585 0) 
(list 4554.585 0) 
(list 4554.585 -605)))
(apply 'command (append '("pline") coords '("c")))
(command "._fillet" "radius" "0" "._fillet" "P" (entlast))
(command "_layer" "set" "window" "")
(command "_rectangle" "4405.415,-1935" "4554.585,-600")
(command "_rectangle" "4405.415,2400" "4554.585,5300")
(command "_layer" "set" "grid" "")
(command "_rectangle" "4406.415,-1934" "4429.9433,-1909.2133")
(command "_array" "last" "" "R" "75" "3" "25.7867" "24.5283")
(command "_rectangle" "4481,-1934" "4504.5283,-1909.2133")
(command "_array" "last" "" "R" "75" "3" "25.7867" "24.5283")
(command "_rectangle" "4406.415,1" "4429.9433,25.7")
(command "_array" "last" "" "R" "70" "3" "25.7" "24.5283")
(command "_rectangle" "4481,1" "4504.5283,25.7")
(command "_array" "last" "" "R" "70" "3" "25.7" "24.5283")
(command "_rectangle" "4406.415,1801" "4429.9433,1825.9185")
(command "_array" "last" "" "R" "135" "3" "25.9185" "24.5283")
(command "_rectangle" "4481,1801" "4504.5283,1825.9185")
(command "_array" "last" "" "R" "135" "3" "25.9185" "24.5283")
(command "_layer" "set" "vgrooveFDA" "")
(command "_rectangle" "4554.585,-2233" "4405.415,-1933")
(command "_layer" "set" "nitride" "")
(command "_layer" "set" "holes" "")
(command "_circle" "4557.085,331.5" "0.5")
(command "_array" "last" "" "R" "379" "1" "3" "2.5")
(command "_circle" "4402.915,331.5" "0.5")
(command "_array" "last" "" "R" "379" "1" "3" "-2.5")
(command "_layer" "set" "nitride" "")
(command "_layer" "set" "window" "")
(command "_layer" "set" "window" "")
(command "_rectangle" "4559.585,0" "4720.415,1800")
(command "._fillet" "radius" "20" "._fillet" "P" (entlast))
(command "_layer" "set" "grid" "")
(command "_rectangle" "4560.585,1" "4582.4179,25.7")
(command "_array" "last" "" "R" "70" "7" "25.7" "22.8329")
(command "_layer" "set" "nitride" "")
; DRAWING REGION LAYER
(command "_layer" "set" "regionLayer14" "")
(command "_rectangle" "4400,-460" "4560,2260")
(command "_layer" "set" "nitride" "")
(setq coupler14 nil)
(setq singlenanobeam14 nil)
(setq anglednodearray14 nil)
(setq cooledsinglenanobeam14 nil)
(setq yjunction14 nil)
; DEVICE #15
(command "_layer" "set" "window" "")
(command "_circle" "4712.915,-415" "5")
(command "_circle" "4712.915,-402.5" "5")
(command "_circle" "4712.915,-390" "5")
(command "_circle" "4712.915,-377.5" "5")
(command "_circle" "4700.415,-415" "5")
(command "_circle" "4700.415,-402.5" "5")
(command "_circle" "4700.415,-390" "5")
(command "_circle" "4700.415,-377.5" "5")
(command "_circle" "4687.915,-415" "5")
(command "_circle" "4687.915,-402.5" "5")
(command "_circle" "4687.915,-390" "5")
(command "_circle" "4687.915,-377.5" "5")
(command "_circle" "4675.415,-415" "5")
(command "_circle" "4675.415,-402.5" "5")
(command "_circle" "4675.415,-390" "5")
(command "_layer" "set" "nitride" "")
(setq currobj nil)
(setq currobj (ssadd))
; DRAWING COUPLER
(setq coords (list 
(list 4800.0615 -415) 
(list 4800.0615 -413) 
(list 4873.585 -413) 
(list 4873.585 -413) 
(list 4873.9677 -413.0761) 
(list 4874.2921 -413.2929) 
(list 4874.5089 -413.6173) 
(list 4874.585 -414) 
(list 4874.585 -411.8) 
(list 4874.585 -411.8) 
(list 4874.5089 -412.1827) 
(list 4874.2921 -412.5071) 
(list 4873.9677 -412.7239) 
(list 4873.585 -412.8) 
(list 4800.0615 -412.8) 
(list 4800.0615 -410.8) 
(list 4799.9385 -410.8) 
(list 4799.9385 -412.8) 
(list 4726.415 -412.8) 
(list 4726.0323 -412.7239) 
(list 4725.7079 -412.5071) 
(list 4725.4911 -412.1827) 
(list 4725.415 -411.8) 
(list 4725.415 -411.8) 
(list 4725.415 -414) 
(list 4725.4911 -413.6173) 
(list 4725.7079 -413.2929) 
(list 4726.0323 -413.0761) 
(list 4726.415 -413) 
(list 4726.415 -413) 
(list 4799.9385 -413) 
(list 4799.9385 -415)))
(apply 'command (append '("pline") coords '("c")))
(setq currobj (ssadd (entlast) currobj))
(command "._fillet" "radius" "0.3" "._fillet" "P" (entlast))
(command "_layer" "set" "holes" "")
(command "_circle" "4800,-412.9" "0.113")
(setq currobj (ssadd (entlast) currobj))
(command "_layer" "set" "nitride" "")
(command "_layer" "set" "text" "")
(command "_circle" "4799.2,-415" "0.075")
(command "_circle" "4799.2,-414.7" "0.075")
(command "_circle" "4799.2,-414.4" "0.075")
(command "_circle" "4798.9,-415" "0.075")
(command "_circle" "4798.9,-414.7" "0.075")
(command "_circle" "4798.9,-414.4" "0.075")
(command "_circle" "4798.6,-415" "0.075")
(command "_circle" "4798.6,-414.7" "0.075")
(command "_circle" "4798.6,-414.4" "0.075")
(command "_layer" "set" "nitride" "")
(command "_layer" "set" "prebias" "")
(command "_rectangle" "4725.415,-414" "4874.585,-411.8")
(setq currobj (ssadd (entlast) currobj))
(command "_rectangle" "4799.9385,-415" "4800.0615,-410.8")
(setq currobj (ssadd (entlast) currobj))
(command "_layer" "set" "nitride" "")
(setq coupler15 currobj)
(setq currobj nil)
(setq currobj (ssadd))
; DRAWING SINGLE NANOBEAM
(setq coords (list 
(list 4800.0615 -410.8) 
(list 4800.0615 -409.1417) 
(list 4800.0615 -407.4833) 
(list 4800.0615 -405.825) 
(list 4800.0615 -404.1667) 
(list 4800.0615 -402.5083) 
(list 4800.0615 -400.85) 
(list 4800.0615 -399.1917) 
(list 4800.0615 -397.5333) 
(list 4800.0616 -395.875) 
(list 4800.0616 -394.2167) 
(list 4800.0616 -392.5583) 
(list 4800.0616 -390.9) 
(list 4800.0617 -389.2417) 
(list 4800.0617 -387.5833) 
(list 4800.0617 -385.925) 
(list 4800.0618 -384.2667) 
(list 4800.0619 -382.6083) 
(list 4800.0619 -380.95) 
(list 4800.062 -379.2917) 
(list 4800.0621 -377.6333) 
(list 4800.0622 -375.975) 
(list 4800.0623 -374.3167) 
(list 4800.0624 -372.6583) 
(list 4800.0625 -371) 
(list 4800.0626 -369.3417) 
(list 4800.0628 -367.6833) 
(list 4800.0629 -366.025) 
(list 4800.0631 -364.3667) 
(list 4800.0632 -362.7083) 
(list 4800.0634 -361.05) 
(list 4800.0636 -359.3917) 
(list 4800.0638 -357.7333) 
(list 4800.0641 -356.075) 
(list 4800.0643 -354.4167) 
(list 4800.0646 -352.7583) 
(list 4800.0648 -351.1) 
(list 4800.0651 -349.4417) 
(list 4800.0654 -347.7833) 
(list 4800.0657 -346.125) 
(list 4800.0661 -344.4667) 
(list 4800.0664 -342.8083) 
(list 4800.0668 -341.15) 
(list 4800.0672 -339.4917) 
(list 4800.0676 -337.8333) 
(list 4800.068 -336.175) 
(list 4800.0685 -334.5167) 
(list 4800.0689 -332.8583) 
(list 4800.0694 -331.2) 
(list 4800.0699 -329.5417) 
(list 4800.0704 -327.8833) 
(list 4800.071 -326.225) 
(list 4800.0715 -324.5667) 
(list 4800.0721 -322.9083) 
(list 4800.0728 -321.25) 
(list 4800.0734 -319.5917) 
(list 4800.0741 -317.9333) 
(list 4800.0747 -316.275) 
(list 4800.0754 -314.6167) 
(list 4800.0762 -312.9583) 
(list 4800.0769 -311.3) 
(list 4800.0777 -309.6417) 
(list 4800.0785 -307.9833) 
(list 4800.0794 -306.325) 
(list 4800.0802 -304.6667) 
(list 4800.0811 -303.0083) 
(list 4800.082 -301.35) 
(list 4800.083 -299.6917) 
(list 4800.084 -298.0333) 
(list 4800.085 -296.375) 
(list 4800.086 -294.7167) 
(list 4800.0871 -293.0583) 
(list 4800.0882 -291.4) 
(list 4800.0893 -289.7417) 
(list 4800.0905 -288.0833) 
(list 4800.0917 -286.425) 
(list 4800.0929 -284.7667) 
(list 4800.0941 -283.1083) 
(list 4800.0954 -281.45) 
(list 4800.0967 -279.7917) 
(list 4800.0981 -278.1333) 
(list 4800.0995 -276.475) 
(list 4800.1009 -274.8167) 
(list 4800.1024 -273.1583) 
(list 4800.1039 -271.5) 
(list 4800.1054 -269.8417) 
(list 4800.107 -268.1833) 
(list 4800.1086 -266.525) 
(list 4800.1102 -264.8667) 
(list 4800.1119 -263.2083) 
(list 4800.1136 -261.55) 
(list 4800.1154 -259.8917) 
(list 4800.1172 -258.2333) 
(list 4800.119 -256.575) 
(list 4800.1209 -254.9167) 
(list 4800.1228 -253.2583) 
(list 4800.1247 -251.6) 
(list 4800.1267 -249.9417) 
(list 4800.1288 -248.2833) 
(list 4800.1308 -246.625) 
(list 4800.133 -244.9667) 
(list 4800.1351 -243.3083) 
(list 4800.1373 -241.65) 
(list 4800.1396 -239.9917) 
(list 4800.1419 -238.3333) 
(list 4800.1442 -236.675) 
(list 4800.1466 -235.0167) 
(list 4800.1491 -233.3583) 
(list 4800.1515 -231.7) 
(list 4800.1541 -230.0417) 
(list 4800.1566 -228.3833) 
(list 4800.1592 -226.725) 
(list 4800.1619 -225.0667) 
(list 4800.1646 -223.4083) 
(list 4800.1674 -221.75) 
(list 4800.1702 -220.0917) 
(list 4800.1731 -218.4333) 
(list 4800.176 -216.775) 
(list 4800.1789 -215.1167) 
(list 4800.1819 -213.4583) 
(list 4800.185 -211.8) 
(list 4799.815 -211.8) 
(list 4799.8181 -213.4583) 
(list 4799.8211 -215.1167) 
(list 4799.824 -216.775) 
(list 4799.8269 -218.4333) 
(list 4799.8298 -220.0917) 
(list 4799.8326 -221.75) 
(list 4799.8354 -223.4083) 
(list 4799.8381 -225.0667) 
(list 4799.8408 -226.725) 
(list 4799.8434 -228.3833) 
(list 4799.8459 -230.0417) 
(list 4799.8485 -231.7) 
(list 4799.8509 -233.3583) 
(list 4799.8534 -235.0167) 
(list 4799.8558 -236.675) 
(list 4799.8581 -238.3333) 
(list 4799.8604 -239.9917) 
(list 4799.8627 -241.65) 
(list 4799.8649 -243.3083) 
(list 4799.867 -244.9667) 
(list 4799.8692 -246.625) 
(list 4799.8712 -248.2833) 
(list 4799.8733 -249.9417) 
(list 4799.8753 -251.6) 
(list 4799.8772 -253.2583) 
(list 4799.8791 -254.9167) 
(list 4799.881 -256.575) 
(list 4799.8828 -258.2333) 
(list 4799.8846 -259.8917) 
(list 4799.8864 -261.55) 
(list 4799.8881 -263.2083) 
(list 4799.8898 -264.8667) 
(list 4799.8914 -266.525) 
(list 4799.893 -268.1833) 
(list 4799.8946 -269.8417) 
(list 4799.8961 -271.5) 
(list 4799.8976 -273.1583) 
(list 4799.8991 -274.8167) 
(list 4799.9005 -276.475) 
(list 4799.9019 -278.1333) 
(list 4799.9033 -279.7917) 
(list 4799.9046 -281.45) 
(list 4799.9059 -283.1083) 
(list 4799.9071 -284.7667) 
(list 4799.9083 -286.425) 
(list 4799.9095 -288.0833) 
(list 4799.9107 -289.7417) 
(list 4799.9118 -291.4) 
(list 4799.9129 -293.0583) 
(list 4799.914 -294.7167) 
(list 4799.915 -296.375) 
(list 4799.916 -298.0333) 
(list 4799.917 -299.6917) 
(list 4799.918 -301.35) 
(list 4799.9189 -303.0083) 
(list 4799.9198 -304.6667) 
(list 4799.9206 -306.325) 
(list 4799.9215 -307.9833) 
(list 4799.9223 -309.6417) 
(list 4799.9231 -311.3) 
(list 4799.9238 -312.9583) 
(list 4799.9246 -314.6167) 
(list 4799.9253 -316.275) 
(list 4799.9259 -317.9333) 
(list 4799.9266 -319.5917) 
(list 4799.9272 -321.25) 
(list 4799.9279 -322.9083) 
(list 4799.9285 -324.5667) 
(list 4799.929 -326.225) 
(list 4799.9296 -327.8833) 
(list 4799.9301 -329.5417) 
(list 4799.9306 -331.2) 
(list 4799.9311 -332.8583) 
(list 4799.9315 -334.5167) 
(list 4799.932 -336.175) 
(list 4799.9324 -337.8333) 
(list 4799.9328 -339.4917) 
(list 4799.9332 -341.15) 
(list 4799.9336 -342.8083) 
(list 4799.9339 -344.4667) 
(list 4799.9343 -346.125) 
(list 4799.9346 -347.7833) 
(list 4799.9349 -349.4417) 
(list 4799.9352 -351.1) 
(list 4799.9354 -352.7583) 
(list 4799.9357 -354.4167) 
(list 4799.9359 -356.075) 
(list 4799.9362 -357.7333) 
(list 4799.9364 -359.3917) 
(list 4799.9366 -361.05) 
(list 4799.9368 -362.7083) 
(list 4799.9369 -364.3667) 
(list 4799.9371 -366.025) 
(list 4799.9372 -367.6833) 
(list 4799.9374 -369.3417) 
(list 4799.9375 -371) 
(list 4799.9376 -372.6583) 
(list 4799.9377 -374.3167) 
(list 4799.9378 -375.975) 
(list 4799.9379 -377.6333) 
(list 4799.938 -379.2917) 
(list 4799.9381 -380.95) 
(list 4799.9381 -382.6083) 
(list 4799.9382 -384.2667) 
(list 4799.9383 -385.925) 
(list 4799.9383 -387.5833) 
(list 4799.9383 -389.2417) 
(list 4799.9384 -390.9) 
(list 4799.9384 -392.5583) 
(list 4799.9384 -394.2167) 
(list 4799.9384 -395.875) 
(list 4799.9385 -397.5333) 
(list 4799.9385 -399.1917) 
(list 4799.9385 -400.85) 
(list 4799.9385 -402.5083) 
(list 4799.9385 -404.1667) 
(list 4799.9385 -405.825) 
(list 4799.9385 -407.4833) 
(list 4799.9385 -409.1417) 
(list 4799.9385 -410.8)))
(apply 'command (append '("pline") coords '("c")))
(setq currobj (ssadd (entlast) currobj))
(command "_layer" "set" "prebias" "")
(command "_rectangle" "4799.815,-410.8" "4800.185,-211.8")
(setq currobj (ssadd (entlast) currobj))
(command "_layer" "set" "nitride" "")
(setq singlenanobeam15 currobj)
(setq currobj nil)
(setq currobj (ssadd))
; DRAWING NODE ARRAY
(setq coords (list 
(list 4800.185 -211.8) 
(list 4800.5625 -201.8) 
(list 4800.5625 -201.8) 
(list 4800.5625 -200.8) 
(list 4874.585 -212.6864) 
(list 4874.585 -207.7434) 
(list 4800.5625 -197.357) 
(list 4800.5625 -196.357) 
(list 4800.5625 -196.357) 
(list 4800.2625 -186.357) 
(list 4799.7375 -186.357) 
(list 4799.4375 -196.357) 
(list 4799.4375 -196.357) 
(list 4799.4375 -197.357) 
(list 4725.415 -207.7434) 
(list 4725.415 -212.6864) 
(list 4799.4375 -200.8) 
(list 4799.4375 -201.8) 
(list 4799.4375 -201.8) 
(list 4799.815 -211.8)))
(apply 'command (append '("pline") coords '("c")))
(setq currobj (ssadd (entlast) currobj))
(command "_layer" "set" "prebias" "")
(setq coords (list 
(list 4799.4375 -212.6864) 
(list 4799.4375 -200.8) 
(list 4725.415 -212.6864) 
(list 4725.415 -207.7434) 
(list 4799.4375 -197.357) 
(list 4799.4375 -186.357) 
(list 4800.5625 -186.357) 
(list 4800.5625 -197.357) 
(list 4874.585 -207.7434) 
(list 4874.585 -212.6864) 
(list 4800.5625 -200.8) 
(list 4800.5625 -212.6864)))
(apply 'command (append '("pline") coords '("c")))
(setq currobj (ssadd (entlast) currobj))
(command "_layer" "set" "nitride" "")
(command "_layer" "set" "fda1" "")
(setq coords (list 
(list 4800.5625 -200.657) 
(list 4874.585 -212.5434) 
(list 4874.585 -212.3664) 
(list 4800.5625 -200.58)))
(apply 'command (append '("pline") coords '("c")))
(setq currobj (ssadd (entlast) currobj))
(setq coords (list 
(list 4800.5625 -200.437) 
(list 4874.585 -212.2234) 
(list 4874.585 -212.0464) 
(list 4800.5625 -200.36)))
(apply 'command (append '("pline") coords '("c")))
(setq currobj (ssadd (entlast) currobj))
(setq coords (list 
(list 4800.5625 -200.217) 
(list 4874.585 -211.9034) 
(list 4874.585 -211.7264) 
(list 4800.5625 -200.14)))
(apply 'command (append '("pline") coords '("c")))
(setq currobj (ssadd (entlast) currobj))
(setq coords (list 
(list 4800.5625 -199.997) 
(list 4874.585 -211.5834) 
(list 4874.585 -211.4064) 
(list 4800.5625 -199.92)))
(apply 'command (append '("pline") coords '("c")))
(setq currobj (ssadd (entlast) currobj))
(setq coords (list 
(list 4800.5625 -199.777) 
(list 4874.585 -211.2634) 
(list 4874.585 -211.0864) 
(list 4800.5625 -199.7)))
(apply 'command (append '("pline") coords '("c")))
(setq currobj (ssadd (entlast) currobj))
(setq coords (list 
(list 4800.5625 -199.557) 
(list 4874.585 -210.9434) 
(list 4874.585 -210.7664) 
(list 4800.5625 -199.48)))
(apply 'command (append '("pline") coords '("c")))
(setq currobj (ssadd (entlast) currobj))
(setq coords (list 
(list 4800.5625 -199.337) 
(list 4874.585 -210.6234) 
(list 4874.585 -210.4464) 
(list 4800.5625 -199.26)))
(apply 'command (append '("pline") coords '("c")))
(setq currobj (ssadd (entlast) currobj))
(setq coords (list 
(list 4800.5625 -199.117) 
(list 4874.585 -210.3034) 
(list 4874.585 -210.1264) 
(list 4800.5625 -199.04)))
(apply 'command (append '("pline") coords '("c")))
(setq currobj (ssadd (entlast) currobj))
(setq coords (list 
(list 4800.5625 -198.897) 
(list 4874.585 -209.9834) 
(list 4874.585 -209.8064) 
(list 4800.5625 -198.82)))
(apply 'command (append '("pline") coords '("c")))
(setq currobj (ssadd (entlast) currobj))
(setq coords (list 
(list 4800.5625 -198.677) 
(list 4874.585 -209.6634) 
(list 4874.585 -209.4864) 
(list 4800.5625 -198.6)))
(apply 'command (append '("pline") coords '("c")))
(setq currobj (ssadd (entlast) currobj))
(setq coords (list 
(list 4800.5625 -198.457) 
(list 4874.585 -209.3434) 
(list 4874.585 -209.1664) 
(list 4800.5625 -198.38)))
(apply 'command (append '("pline") coords '("c")))
(setq currobj (ssadd (entlast) currobj))
(setq coords (list 
(list 4800.5625 -198.237) 
(list 4874.585 -209.0234) 
(list 4874.585 -208.8464) 
(list 4800.5625 -198.16)))
(apply 'command (append '("pline") coords '("c")))
(setq currobj (ssadd (entlast) currobj))
(setq coords (list 
(list 4800.5625 -198.017) 
(list 4874.585 -208.7034) 
(list 4874.585 -208.5264) 
(list 4800.5625 -197.94)))
(apply 'command (append '("pline") coords '("c")))
(setq currobj (ssadd (entlast) currobj))
(setq coords (list 
(list 4800.5625 -197.797) 
(list 4874.585 -208.3834) 
(list 4874.585 -208.2064) 
(list 4800.5625 -197.72)))
(apply 'command (append '("pline") coords '("c")))
(setq currobj (ssadd (entlast) currobj))
(setq coords (list 
(list 4800.5625 -197.577) 
(list 4874.585 -208.0634) 
(list 4874.585 -207.8864) 
(list 4800.5625 -197.5)))
(apply 'command (append '("pline") coords '("c")))
(setq currobj (ssadd (entlast) currobj))
(setq coords (list 
(list 4799.4375 -197.5) 
(list 4725.415 -207.8864) 
(list 4725.415 -208.0634) 
(list 4799.4375 -197.577)))
(apply 'command (append '("pline") coords '("c")))
(setq currobj (ssadd (entlast) currobj))
(setq coords (list 
(list 4799.4375 -197.72) 
(list 4725.415 -208.2064) 
(list 4725.415 -208.3834) 
(list 4799.4375 -197.797)))
(apply 'command (append '("pline") coords '("c")))
(setq currobj (ssadd (entlast) currobj))
(setq coords (list 
(list 4799.4375 -197.94) 
(list 4725.415 -208.5264) 
(list 4725.415 -208.7034) 
(list 4799.4375 -198.017)))
(apply 'command (append '("pline") coords '("c")))
(setq currobj (ssadd (entlast) currobj))
(setq coords (list 
(list 4799.4375 -198.16) 
(list 4725.415 -208.8464) 
(list 4725.415 -209.0234) 
(list 4799.4375 -198.237)))
(apply 'command (append '("pline") coords '("c")))
(setq currobj (ssadd (entlast) currobj))
(setq coords (list 
(list 4799.4375 -198.38) 
(list 4725.415 -209.1664) 
(list 4725.415 -209.3434) 
(list 4799.4375 -198.457)))
(apply 'command (append '("pline") coords '("c")))
(setq currobj (ssadd (entlast) currobj))
(setq coords (list 
(list 4799.4375 -198.6) 
(list 4725.415 -209.4864) 
(list 4725.415 -209.6634) 
(list 4799.4375 -198.677)))
(apply 'command (append '("pline") coords '("c")))
(setq currobj (ssadd (entlast) currobj))
(setq coords (list 
(list 4799.4375 -198.82) 
(list 4725.415 -209.8064) 
(list 4725.415 -209.9834) 
(list 4799.4375 -198.897)))
(apply 'command (append '("pline") coords '("c")))
(setq currobj (ssadd (entlast) currobj))
(setq coords (list 
(list 4799.4375 -199.04) 
(list 4725.415 -210.1264) 
(list 4725.415 -210.3034) 
(list 4799.4375 -199.117)))
(apply 'command (append '("pline") coords '("c")))
(setq currobj (ssadd (entlast) currobj))
(setq coords (list 
(list 4799.4375 -199.26) 
(list 4725.415 -210.4464) 
(list 4725.415 -210.6234) 
(list 4799.4375 -199.337)))
(apply 'command (append '("pline") coords '("c")))
(setq currobj (ssadd (entlast) currobj))
(setq coords (list 
(list 4799.4375 -199.48) 
(list 4725.415 -210.7664) 
(list 4725.415 -210.9434) 
(list 4799.4375 -199.557)))
(apply 'command (append '("pline") coords '("c")))
(setq currobj (ssadd (entlast) currobj))
(setq coords (list 
(list 4799.4375 -199.7) 
(list 4725.415 -211.0864) 
(list 4725.415 -211.2634) 
(list 4799.4375 -199.777)))
(apply 'command (append '("pline") coords '("c")))
(setq currobj (ssadd (entlast) currobj))
(setq coords (list 
(list 4799.4375 -199.92) 
(list 4725.415 -211.4064) 
(list 4725.415 -211.5834) 
(list 4799.4375 -199.997)))
(apply 'command (append '("pline") coords '("c")))
(setq currobj (ssadd (entlast) currobj))
(setq coords (list 
(list 4799.4375 -200.14) 
(list 4725.415 -211.7264) 
(list 4725.415 -211.9034) 
(list 4799.4375 -200.217)))
(apply 'command (append '("pline") coords '("c")))
(setq currobj (ssadd (entlast) currobj))
(setq coords (list 
(list 4799.4375 -200.36) 
(list 4725.415 -212.0464) 
(list 4725.415 -212.2234) 
(list 4799.4375 -200.437)))
(apply 'command (append '("pline") coords '("c")))
(setq currobj (ssadd (entlast) currobj))
(setq coords (list 
(list 4799.4375 -200.58) 
(list 4725.415 -212.3664) 
(list 4725.415 -212.5434) 
(list 4799.4375 -200.657)))
(apply 'command (append '("pline") coords '("c")))
(setq currobj (ssadd (entlast) currobj))
(command "_layer" "set" "nitride" "")
(command "_layer" "set" "text" "")
(command "_circle" "4798.985,-211.8" "0.075")
(command "_circle" "4798.985,-211.5" "0.075")
(command "_circle" "4798.985,-211.2" "0.075")
(command "_circle" "4798.985,-210.9" "0.075")
(command "_circle" "4798.985,-210.6" "0.075")
(command "_circle" "4798.685,-211.8" "0.075")
(command "_circle" "4798.685,-211.5" "0.075")
(command "_circle" "4798.685,-211.2" "0.075")
(command "_circle" "4798.685,-210.9" "0.075")
(command "_circle" "4798.685,-210.6" "0.075")
(command "_circle" "4798.385,-211.8" "0.075")
(command "_circle" "4798.385,-211.5" "0.075")
(command "_circle" "4798.385,-211.2" "0.075")
(command "_circle" "4798.385,-210.9" "0.075")
(command "_circle" "4798.385,-210.6" "0.075")
(command "_circle" "4798.085,-211.8" "0.075")
(command "_circle" "4798.085,-211.5" "0.075")
(command "_circle" "4798.085,-211.2" "0.075")
(command "_circle" "4798.085,-210.9" "0.075")
(command "_circle" "4798.085,-210.6" "0.075")
(command "_circle" "4797.785,-211.8" "0.075")
(command "_circle" "4797.785,-211.5" "0.075")
(command "_circle" "4797.785,-211.2" "0.075")
(command "_circle" "4797.785,-210.9" "0.075")
(command "_circle" "4797.785,-210.6" "0.075")
(command "_layer" "set" "nitride" "")
(setq anglednodearray15 currobj)
(setq currobj nil)
(setq currobj (ssadd))
; DRAWING COOLED SINGLE NANOBEAM
(setq coords (list 
(list 4800.2625 -186.357) 
(list 4800.2625 -181.357) 
(list 4799.7375 -181.357) 
(list 4799.7375 -186.357)))
(apply 'command (append '("pline") coords '("c")))
(setq currobj (ssadd (entlast) currobj))
(command "_layer" "set" "prebias" "")
(command "_rectangle" "4799.7375,-186.357" "4800.2625,-181.357")
(setq currobj (ssadd (entlast) currobj))
(command "_layer" "set" "nitride" "")
(setq coords (list 
(list 4800.2625 -181.357) 
(list 4800.5625 -171.357) 
(list 4800.5625 -171.357) 
(list 4800.5625 -170.357) 
(list 4874.585 -171.107) 
(list 4874.585 -166.164) 
(list 4800.5625 -166.914) 
(list 4800.5625 -165.914) 
(list 4800.5625 -165.914) 
(list 4800.2625 -155.914) 
(list 4799.7375 -155.914) 
(list 4799.4375 -165.914) 
(list 4799.4375 -165.914) 
(list 4799.4375 -166.914) 
(list 4725.415 -166.164) 
(list 4725.415 -171.107) 
(list 4799.4375 -170.357) 
(list 4799.4375 -171.357) 
(list 4799.4375 -171.357) 
(list 4799.7375 -181.357)))
(apply 'command (append '("pline") coords '("c")))
(setq currobj (ssadd (entlast) currobj))
(command "_layer" "set" "prebias" "")
(setq coords (list 
(list 4799.4375 -181.357) 
(list 4799.4375 -170.357) 
(list 4725.415 -171.107) 
(list 4725.415 -166.164) 
(list 4799.4375 -166.914) 
(list 4799.4375 -155.914) 
(list 4800.5625 -155.914) 
(list 4800.5625 -166.914) 
(list 4874.585 -166.164) 
(list 4874.585 -171.107) 
(list 4800.5625 -170.357) 
(list 4800.5625 -181.357)))
(apply 'command (append '("pline") coords '("c")))
(setq currobj (ssadd (entlast) currobj))
(command "_layer" "set" "nitride" "")
(command "_layer" "set" "fda1" "")
(setq coords (list 
(list 4800.5625 -170.214) 
(list 4874.585 -170.964) 
(list 4874.585 -170.787) 
(list 4800.5625 -170.137)))
(apply 'command (append '("pline") coords '("c")))
(setq currobj (ssadd (entlast) currobj))
(setq coords (list 
(list 4800.5625 -169.994) 
(list 4874.585 -170.644) 
(list 4874.585 -170.467) 
(list 4800.5625 -169.917)))
(apply 'command (append '("pline") coords '("c")))
(setq currobj (ssadd (entlast) currobj))
(setq coords (list 
(list 4800.5625 -169.774) 
(list 4874.585 -170.324) 
(list 4874.585 -170.147) 
(list 4800.5625 -169.697)))
(apply 'command (append '("pline") coords '("c")))
(setq currobj (ssadd (entlast) currobj))
(setq coords (list 
(list 4800.5625 -169.554) 
(list 4874.585 -170.004) 
(list 4874.585 -169.827) 
(list 4800.5625 -169.477)))
(apply 'command (append '("pline") coords '("c")))
(setq currobj (ssadd (entlast) currobj))
(setq coords (list 
(list 4800.5625 -169.334) 
(list 4874.585 -169.684) 
(list 4874.585 -169.507) 
(list 4800.5625 -169.257)))
(apply 'command (append '("pline") coords '("c")))
(setq currobj (ssadd (entlast) currobj))
(setq coords (list 
(list 4800.5625 -169.114) 
(list 4874.585 -169.364) 
(list 4874.585 -169.187) 
(list 4800.5625 -169.037)))
(apply 'command (append '("pline") coords '("c")))
(setq currobj (ssadd (entlast) currobj))
(setq coords (list 
(list 4800.5625 -168.894) 
(list 4874.585 -169.044) 
(list 4874.585 -168.867) 
(list 4800.5625 -168.817)))
(apply 'command (append '("pline") coords '("c")))
(setq currobj (ssadd (entlast) currobj))
(setq coords (list 
(list 4800.5625 -168.674) 
(list 4874.585 -168.724) 
(list 4874.585 -168.547) 
(list 4800.5625 -168.597)))
(apply 'command (append '("pline") coords '("c")))
(setq currobj (ssadd (entlast) currobj))
(setq coords (list 
(list 4800.5625 -168.454) 
(list 4874.585 -168.404) 
(list 4874.585 -168.227) 
(list 4800.5625 -168.377)))
(apply 'command (append '("pline") coords '("c")))
(setq currobj (ssadd (entlast) currobj))
(setq coords (list 
(list 4800.5625 -168.234) 
(list 4874.585 -168.084) 
(list 4874.585 -167.907) 
(list 4800.5625 -168.157)))
(apply 'command (append '("pline") coords '("c")))
(setq currobj (ssadd (entlast) currobj))
(setq coords (list 
(list 4800.5625 -168.014) 
(list 4874.585 -167.764) 
(list 4874.585 -167.587) 
(list 4800.5625 -167.937)))
(apply 'command (append '("pline") coords '("c")))
(setq currobj (ssadd (entlast) currobj))
(setq coords (list 
(list 4800.5625 -167.794) 
(list 4874.585 -167.444) 
(list 4874.585 -167.267) 
(list 4800.5625 -167.717)))
(apply 'command (append '("pline") coords '("c")))
(setq currobj (ssadd (entlast) currobj))
(setq coords (list 
(list 4800.5625 -167.574) 
(list 4874.585 -167.124) 
(list 4874.585 -166.947) 
(list 4800.5625 -167.497)))
(apply 'command (append '("pline") coords '("c")))
(setq currobj (ssadd (entlast) currobj))
(setq coords (list 
(list 4800.5625 -167.354) 
(list 4874.585 -166.804) 
(list 4874.585 -166.627) 
(list 4800.5625 -167.277)))
(apply 'command (append '("pline") coords '("c")))
(setq currobj (ssadd (entlast) currobj))
(setq coords (list 
(list 4800.5625 -167.134) 
(list 4874.585 -166.484) 
(list 4874.585 -166.307) 
(list 4800.5625 -167.057)))
(apply 'command (append '("pline") coords '("c")))
(setq currobj (ssadd (entlast) currobj))
(setq coords (list 
(list 4799.4375 -167.057) 
(list 4725.415 -166.307) 
(list 4725.415 -166.484) 
(list 4799.4375 -167.134)))
(apply 'command (append '("pline") coords '("c")))
(setq currobj (ssadd (entlast) currobj))
(setq coords (list 
(list 4799.4375 -167.277) 
(list 4725.415 -166.627) 
(list 4725.415 -166.804) 
(list 4799.4375 -167.354)))
(apply 'command (append '("pline") coords '("c")))
(setq currobj (ssadd (entlast) currobj))
(setq coords (list 
(list 4799.4375 -167.497) 
(list 4725.415 -166.947) 
(list 4725.415 -167.124) 
(list 4799.4375 -167.574)))
(apply 'command (append '("pline") coords '("c")))
(setq currobj (ssadd (entlast) currobj))
(setq coords (list 
(list 4799.4375 -167.717) 
(list 4725.415 -167.267) 
(list 4725.415 -167.444) 
(list 4799.4375 -167.794)))
(apply 'command (append '("pline") coords '("c")))
(setq currobj (ssadd (entlast) currobj))
(setq coords (list 
(list 4799.4375 -167.937) 
(list 4725.415 -167.587) 
(list 4725.415 -167.764) 
(list 4799.4375 -168.014)))
(apply 'command (append '("pline") coords '("c")))
(setq currobj (ssadd (entlast) currobj))
(setq coords (list 
(list 4799.4375 -168.157) 
(list 4725.415 -167.907) 
(list 4725.415 -168.084) 
(list 4799.4375 -168.234)))
(apply 'command (append '("pline") coords '("c")))
(setq currobj (ssadd (entlast) currobj))
(setq coords (list 
(list 4799.4375 -168.377) 
(list 4725.415 -168.227) 
(list 4725.415 -168.404) 
(list 4799.4375 -168.454)))
(apply 'command (append '("pline") coords '("c")))
(setq currobj (ssadd (entlast) currobj))
(setq coords (list 
(list 4799.4375 -168.597) 
(list 4725.415 -168.547) 
(list 4725.415 -168.724) 
(list 4799.4375 -168.674)))
(apply 'command (append '("pline") coords '("c")))
(setq currobj (ssadd (entlast) currobj))
(setq coords (list 
(list 4799.4375 -168.817) 
(list 4725.415 -168.867) 
(list 4725.415 -169.044) 
(list 4799.4375 -168.894)))
(apply 'command (append '("pline") coords '("c")))
(setq currobj (ssadd (entlast) currobj))
(setq coords (list 
(list 4799.4375 -169.037) 
(list 4725.415 -169.187) 
(list 4725.415 -169.364) 
(list 4799.4375 -169.114)))
(apply 'command (append '("pline") coords '("c")))
(setq currobj (ssadd (entlast) currobj))
(setq coords (list 
(list 4799.4375 -169.257) 
(list 4725.415 -169.507) 
(list 4725.415 -169.684) 
(list 4799.4375 -169.334)))
(apply 'command (append '("pline") coords '("c")))
(setq currobj (ssadd (entlast) currobj))
(setq coords (list 
(list 4799.4375 -169.477) 
(list 4725.415 -169.827) 
(list 4725.415 -170.004) 
(list 4799.4375 -169.554)))
(apply 'command (append '("pline") coords '("c")))
(setq currobj (ssadd (entlast) currobj))
(setq coords (list 
(list 4799.4375 -169.697) 
(list 4725.415 -170.147) 
(list 4725.415 -170.324) 
(list 4799.4375 -169.774)))
(apply 'command (append '("pline") coords '("c")))
(setq currobj (ssadd (entlast) currobj))
(setq coords (list 
(list 4799.4375 -169.917) 
(list 4725.415 -170.467) 
(list 4725.415 -170.644) 
(list 4799.4375 -169.994)))
(apply 'command (append '("pline") coords '("c")))
(setq currobj (ssadd (entlast) currobj))
(setq coords (list 
(list 4799.4375 -170.137) 
(list 4725.415 -170.787) 
(list 4725.415 -170.964) 
(list 4799.4375 -170.214)))
(apply 'command (append '("pline") coords '("c")))
(setq currobj (ssadd (entlast) currobj))
(command "_layer" "set" "nitride" "")
(command "_layer" "set" "text" "")
(command "_circle" "4799.0625,-181.357" "0.075")
(command "_circle" "4799.0625,-181.057" "0.075")
(command "_circle" "4799.0625,-180.757" "0.075")
(command "_circle" "4799.0625,-180.457" "0.075")
(command "_circle" "4799.0625,-180.157" "0.075")
(command "_circle" "4798.7625,-181.357" "0.075")
(command "_circle" "4798.7625,-181.057" "0.075")
(command "_circle" "4798.7625,-180.757" "0.075")
(command "_circle" "4798.7625,-180.457" "0.075")
(command "_circle" "4798.7625,-180.157" "0.075")
(command "_circle" "4798.4625,-181.357" "0.075")
(command "_circle" "4798.4625,-181.057" "0.075")
(command "_circle" "4798.4625,-180.757" "0.075")
(command "_circle" "4798.4625,-180.457" "0.075")
(command "_circle" "4798.4625,-180.157" "0.075")
(command "_circle" "4798.1625,-181.357" "0.075")
(command "_circle" "4798.1625,-181.057" "0.075")
(command "_circle" "4798.1625,-180.757" "0.075")
(command "_circle" "4798.1625,-180.457" "0.075")
(command "_circle" "4798.1625,-180.157" "0.075")
(command "_circle" "4797.8625,-181.357" "0.075")
(command "_circle" "4797.8625,-181.057" "0.075")
(command "_circle" "4797.8625,-180.757" "0.075")
(command "_circle" "4797.8625,-180.457" "0.075")
(command "_circle" "4797.8625,-180.157" "0.075")
(command "_layer" "set" "nitride" "")
(setq coords (list 
(list 4800.2625 -155.914) 
(list 4800.2625 -40.2693) 
(list 4799.7375 -40.2693) 
(list 4799.7375 -155.914)))
(apply 'command (append '("pline") coords '("c")))
(setq currobj (ssadd (entlast) currobj))
(command "_layer" "set" "prebias" "")
(command "_rectangle" "4799.7375,-155.914" "4800.2625,-40.2693")
(setq currobj (ssadd (entlast) currobj))
(command "_layer" "set" "nitride" "")
(setq coords (list 
(list 4800.2625 -40.2693) 
(list 4800.5625 -30.2693) 
(list 4800.5625 -30.2693) 
(list 4800.5625 -29.2693) 
(list 4874.585 -30.0193) 
(list 4874.585 -25.0763) 
(list 4800.5625 -25.8263) 
(list 4800.5625 -24.8263) 
(list 4800.5625 -24.8263) 
(list 4800.2625 -14.8263) 
(list 4799.7375 -14.8263) 
(list 4799.4375 -24.8263) 
(list 4799.4375 -24.8263) 
(list 4799.4375 -25.8263) 
(list 4725.415 -25.0763) 
(list 4725.415 -30.0193) 
(list 4799.4375 -29.2693) 
(list 4799.4375 -30.2693) 
(list 4799.4375 -30.2693) 
(list 4799.7375 -40.2693)))
(apply 'command (append '("pline") coords '("c")))
(setq currobj (ssadd (entlast) currobj))
(command "_layer" "set" "prebias" "")
(setq coords (list 
(list 4799.4375 -40.2693) 
(list 4799.4375 -29.2693) 
(list 4725.415 -30.0193) 
(list 4725.415 -25.0763) 
(list 4799.4375 -25.8263) 
(list 4799.4375 -14.8263) 
(list 4800.5625 -14.8263) 
(list 4800.5625 -25.8263) 
(list 4874.585 -25.0763) 
(list 4874.585 -30.0193) 
(list 4800.5625 -29.2693) 
(list 4800.5625 -40.2693)))
(apply 'command (append '("pline") coords '("c")))
(setq currobj (ssadd (entlast) currobj))
(command "_layer" "set" "nitride" "")
(command "_layer" "set" "fda1" "")
(setq coords (list 
(list 4800.5625 -29.1263) 
(list 4874.585 -29.8763) 
(list 4874.585 -29.6993) 
(list 4800.5625 -29.0493)))
(apply 'command (append '("pline") coords '("c")))
(setq currobj (ssadd (entlast) currobj))
(setq coords (list 
(list 4800.5625 -28.9063) 
(list 4874.585 -29.5563) 
(list 4874.585 -29.3793) 
(list 4800.5625 -28.8293)))
(apply 'command (append '("pline") coords '("c")))
(setq currobj (ssadd (entlast) currobj))
(setq coords (list 
(list 4800.5625 -28.6863) 
(list 4874.585 -29.2363) 
(list 4874.585 -29.0593) 
(list 4800.5625 -28.6093)))
(apply 'command (append '("pline") coords '("c")))
(setq currobj (ssadd (entlast) currobj))
(setq coords (list 
(list 4800.5625 -28.4663) 
(list 4874.585 -28.9163) 
(list 4874.585 -28.7393) 
(list 4800.5625 -28.3893)))
(apply 'command (append '("pline") coords '("c")))
(setq currobj (ssadd (entlast) currobj))
(setq coords (list 
(list 4800.5625 -28.2463) 
(list 4874.585 -28.5963) 
(list 4874.585 -28.4193) 
(list 4800.5625 -28.1693)))
(apply 'command (append '("pline") coords '("c")))
(setq currobj (ssadd (entlast) currobj))
(setq coords (list 
(list 4800.5625 -28.0263) 
(list 4874.585 -28.2763) 
(list 4874.585 -28.0993) 
(list 4800.5625 -27.9493)))
(apply 'command (append '("pline") coords '("c")))
(setq currobj (ssadd (entlast) currobj))
(setq coords (list 
(list 4800.5625 -27.8063) 
(list 4874.585 -27.9563) 
(list 4874.585 -27.7793) 
(list 4800.5625 -27.7293)))
(apply 'command (append '("pline") coords '("c")))
(setq currobj (ssadd (entlast) currobj))
(setq coords (list 
(list 4800.5625 -27.5863) 
(list 4874.585 -27.6363) 
(list 4874.585 -27.4593) 
(list 4800.5625 -27.5093)))
(apply 'command (append '("pline") coords '("c")))
(setq currobj (ssadd (entlast) currobj))
(setq coords (list 
(list 4800.5625 -27.3663) 
(list 4874.585 -27.3163) 
(list 4874.585 -27.1393) 
(list 4800.5625 -27.2893)))
(apply 'command (append '("pline") coords '("c")))
(setq currobj (ssadd (entlast) currobj))
(setq coords (list 
(list 4800.5625 -27.1463) 
(list 4874.585 -26.9963) 
(list 4874.585 -26.8193) 
(list 4800.5625 -27.0693)))
(apply 'command (append '("pline") coords '("c")))
(setq currobj (ssadd (entlast) currobj))
(setq coords (list 
(list 4800.5625 -26.9263) 
(list 4874.585 -26.6763) 
(list 4874.585 -26.4993) 
(list 4800.5625 -26.8493)))
(apply 'command (append '("pline") coords '("c")))
(setq currobj (ssadd (entlast) currobj))
(setq coords (list 
(list 4800.5625 -26.7063) 
(list 4874.585 -26.3563) 
(list 4874.585 -26.1793) 
(list 4800.5625 -26.6293)))
(apply 'command (append '("pline") coords '("c")))
(setq currobj (ssadd (entlast) currobj))
(setq coords (list 
(list 4800.5625 -26.4863) 
(list 4874.585 -26.0363) 
(list 4874.585 -25.8593) 
(list 4800.5625 -26.4093)))
(apply 'command (append '("pline") coords '("c")))
(setq currobj (ssadd (entlast) currobj))
(setq coords (list 
(list 4800.5625 -26.2663) 
(list 4874.585 -25.7163) 
(list 4874.585 -25.5393) 
(list 4800.5625 -26.1893)))
(apply 'command (append '("pline") coords '("c")))
(setq currobj (ssadd (entlast) currobj))
(setq coords (list 
(list 4800.5625 -26.0463) 
(list 4874.585 -25.3963) 
(list 4874.585 -25.2193) 
(list 4800.5625 -25.9693)))
(apply 'command (append '("pline") coords '("c")))
(setq currobj (ssadd (entlast) currobj))
(setq coords (list 
(list 4799.4375 -25.9693) 
(list 4725.415 -25.2193) 
(list 4725.415 -25.3963) 
(list 4799.4375 -26.0463)))
(apply 'command (append '("pline") coords '("c")))
(setq currobj (ssadd (entlast) currobj))
(setq coords (list 
(list 4799.4375 -26.1893) 
(list 4725.415 -25.5393) 
(list 4725.415 -25.7163) 
(list 4799.4375 -26.2663)))
(apply 'command (append '("pline") coords '("c")))
(setq currobj (ssadd (entlast) currobj))
(setq coords (list 
(list 4799.4375 -26.4093) 
(list 4725.415 -25.8593) 
(list 4725.415 -26.0363) 
(list 4799.4375 -26.4863)))
(apply 'command (append '("pline") coords '("c")))
(setq currobj (ssadd (entlast) currobj))
(setq coords (list 
(list 4799.4375 -26.6293) 
(list 4725.415 -26.1793) 
(list 4725.415 -26.3563) 
(list 4799.4375 -26.7063)))
(apply 'command (append '("pline") coords '("c")))
(setq currobj (ssadd (entlast) currobj))
(setq coords (list 
(list 4799.4375 -26.8493) 
(list 4725.415 -26.4993) 
(list 4725.415 -26.6763) 
(list 4799.4375 -26.9263)))
(apply 'command (append '("pline") coords '("c")))
(setq currobj (ssadd (entlast) currobj))
(setq coords (list 
(list 4799.4375 -27.0693) 
(list 4725.415 -26.8193) 
(list 4725.415 -26.9963) 
(list 4799.4375 -27.1463)))
(apply 'command (append '("pline") coords '("c")))
(setq currobj (ssadd (entlast) currobj))
(setq coords (list 
(list 4799.4375 -27.2893) 
(list 4725.415 -27.1393) 
(list 4725.415 -27.3163) 
(list 4799.4375 -27.3663)))
(apply 'command (append '("pline") coords '("c")))
(setq currobj (ssadd (entlast) currobj))
(setq coords (list 
(list 4799.4375 -27.5093) 
(list 4725.415 -27.4593) 
(list 4725.415 -27.6363) 
(list 4799.4375 -27.5863)))
(apply 'command (append '("pline") coords '("c")))
(setq currobj (ssadd (entlast) currobj))
(setq coords (list 
(list 4799.4375 -27.7293) 
(list 4725.415 -27.7793) 
(list 4725.415 -27.9563) 
(list 4799.4375 -27.8063)))
(apply 'command (append '("pline") coords '("c")))
(setq currobj (ssadd (entlast) currobj))
(setq coords (list 
(list 4799.4375 -27.9493) 
(list 4725.415 -28.0993) 
(list 4725.415 -28.2763) 
(list 4799.4375 -28.0263)))
(apply 'command (append '("pline") coords '("c")))
(setq currobj (ssadd (entlast) currobj))
(setq coords (list 
(list 4799.4375 -28.1693) 
(list 4725.415 -28.4193) 
(list 4725.415 -28.5963) 
(list 4799.4375 -28.2463)))
(apply 'command (append '("pline") coords '("c")))
(setq currobj (ssadd (entlast) currobj))
(setq coords (list 
(list 4799.4375 -28.3893) 
(list 4725.415 -28.7393) 
(list 4725.415 -28.9163) 
(list 4799.4375 -28.4663)))
(apply 'command (append '("pline") coords '("c")))
(setq currobj (ssadd (entlast) currobj))
(setq coords (list 
(list 4799.4375 -28.6093) 
(list 4725.415 -29.0593) 
(list 4725.415 -29.2363) 
(list 4799.4375 -28.6863)))
(apply 'command (append '("pline") coords '("c")))
(setq currobj (ssadd (entlast) currobj))
(setq coords (list 
(list 4799.4375 -28.8293) 
(list 4725.415 -29.3793) 
(list 4725.415 -29.5563) 
(list 4799.4375 -28.9063)))
(apply 'command (append '("pline") coords '("c")))
(setq currobj (ssadd (entlast) currobj))
(setq coords (list 
(list 4799.4375 -29.0493) 
(list 4725.415 -29.6993) 
(list 4725.415 -29.8763) 
(list 4799.4375 -29.1263)))
(apply 'command (append '("pline") coords '("c")))
(setq currobj (ssadd (entlast) currobj))
(command "_layer" "set" "nitride" "")
(command "_layer" "set" "text" "")
(command "_circle" "4799.0625,-40.2693" "0.075")
(command "_circle" "4799.0625,-39.9693" "0.075")
(command "_circle" "4799.0625,-39.6693" "0.075")
(command "_circle" "4799.0625,-39.3693" "0.075")
(command "_circle" "4799.0625,-39.0693" "0.075")
(command "_circle" "4798.7625,-40.2693" "0.075")
(command "_circle" "4798.7625,-39.9693" "0.075")
(command "_circle" "4798.7625,-39.6693" "0.075")
(command "_circle" "4798.7625,-39.3693" "0.075")
(command "_circle" "4798.7625,-39.0693" "0.075")
(command "_circle" "4798.4625,-40.2693" "0.075")
(command "_circle" "4798.4625,-39.9693" "0.075")
(command "_circle" "4798.4625,-39.6693" "0.075")
(command "_circle" "4798.4625,-39.3693" "0.075")
(command "_circle" "4798.4625,-39.0693" "0.075")
(command "_circle" "4798.1625,-40.2693" "0.075")
(command "_circle" "4798.1625,-39.9693" "0.075")
(command "_circle" "4798.1625,-39.6693" "0.075")
(command "_circle" "4798.1625,-39.3693" "0.075")
(command "_circle" "4798.1625,-39.0693" "0.075")
(command "_circle" "4797.8625,-40.2693" "0.075")
(command "_circle" "4797.8625,-39.9693" "0.075")
(command "_circle" "4797.8625,-39.6693" "0.075")
(command "_circle" "4797.8625,-39.3693" "0.075")
(command "_circle" "4797.8625,-39.0693" "0.075")
(command "_layer" "set" "nitride" "")
(setq coords (list 
(list 4800.2625 -14.8263) 
(list 4800.2625 100.8184) 
(list 4799.7375 100.8184) 
(list 4799.7375 -14.8263)))
(apply 'command (append '("pline") coords '("c")))
(setq currobj (ssadd (entlast) currobj))
(command "_layer" "set" "prebias" "")
(command "_rectangle" "4799.7375,-14.8263" "4800.2625,100.8184")
(setq currobj (ssadd (entlast) currobj))
(command "_layer" "set" "nitride" "")
(setq coords (list 
(list 4800.2625 100.8184) 
(list 4800.5625 110.8184) 
(list 4800.5625 110.8184) 
(list 4800.5625 111.8184) 
(list 4874.585 111.0684) 
(list 4874.585 116.0114) 
(list 4800.5625 115.2614) 
(list 4800.5625 116.2614) 
(list 4800.5625 116.2614) 
(list 4800.2625 126.2614) 
(list 4799.7375 126.2614) 
(list 4799.4375 116.2614) 
(list 4799.4375 116.2614) 
(list 4799.4375 115.2614) 
(list 4725.415 116.0114) 
(list 4725.415 111.0684) 
(list 4799.4375 111.8184) 
(list 4799.4375 110.8184) 
(list 4799.4375 110.8184) 
(list 4799.7375 100.8184)))
(apply 'command (append '("pline") coords '("c")))
(setq currobj (ssadd (entlast) currobj))
(command "_layer" "set" "prebias" "")
(setq coords (list 
(list 4799.4375 100.8184) 
(list 4799.4375 111.8184) 
(list 4725.415 111.0684) 
(list 4725.415 116.0114) 
(list 4799.4375 115.2614) 
(list 4799.4375 126.2614) 
(list 4800.5625 126.2614) 
(list 4800.5625 115.2614) 
(list 4874.585 116.0114) 
(list 4874.585 111.0684) 
(list 4800.5625 111.8184) 
(list 4800.5625 100.8184)))
(apply 'command (append '("pline") coords '("c")))
(setq currobj (ssadd (entlast) currobj))
(command "_layer" "set" "nitride" "")
(command "_layer" "set" "fda1" "")
(setq coords (list 
(list 4800.5625 111.9614) 
(list 4874.585 111.2114) 
(list 4874.585 111.3884) 
(list 4800.5625 112.0384)))
(apply 'command (append '("pline") coords '("c")))
(setq currobj (ssadd (entlast) currobj))
(setq coords (list 
(list 4800.5625 112.1814) 
(list 4874.585 111.5314) 
(list 4874.585 111.7084) 
(list 4800.5625 112.2584)))
(apply 'command (append '("pline") coords '("c")))
(setq currobj (ssadd (entlast) currobj))
(setq coords (list 
(list 4800.5625 112.4014) 
(list 4874.585 111.8514) 
(list 4874.585 112.0284) 
(list 4800.5625 112.4784)))
(apply 'command (append '("pline") coords '("c")))
(setq currobj (ssadd (entlast) currobj))
(setq coords (list 
(list 4800.5625 112.6214) 
(list 4874.585 112.1714) 
(list 4874.585 112.3484) 
(list 4800.5625 112.6984)))
(apply 'command (append '("pline") coords '("c")))
(setq currobj (ssadd (entlast) currobj))
(setq coords (list 
(list 4800.5625 112.8414) 
(list 4874.585 112.4914) 
(list 4874.585 112.6684) 
(list 4800.5625 112.9184)))
(apply 'command (append '("pline") coords '("c")))
(setq currobj (ssadd (entlast) currobj))
(setq coords (list 
(list 4800.5625 113.0614) 
(list 4874.585 112.8114) 
(list 4874.585 112.9884) 
(list 4800.5625 113.1384)))
(apply 'command (append '("pline") coords '("c")))
(setq currobj (ssadd (entlast) currobj))
(setq coords (list 
(list 4800.5625 113.2814) 
(list 4874.585 113.1314) 
(list 4874.585 113.3084) 
(list 4800.5625 113.3584)))
(apply 'command (append '("pline") coords '("c")))
(setq currobj (ssadd (entlast) currobj))
(setq coords (list 
(list 4800.5625 113.5014) 
(list 4874.585 113.4514) 
(list 4874.585 113.6284) 
(list 4800.5625 113.5784)))
(apply 'command (append '("pline") coords '("c")))
(setq currobj (ssadd (entlast) currobj))
(setq coords (list 
(list 4800.5625 113.7214) 
(list 4874.585 113.7714) 
(list 4874.585 113.9484) 
(list 4800.5625 113.7984)))
(apply 'command (append '("pline") coords '("c")))
(setq currobj (ssadd (entlast) currobj))
(setq coords (list 
(list 4800.5625 113.9414) 
(list 4874.585 114.0914) 
(list 4874.585 114.2684) 
(list 4800.5625 114.0184)))
(apply 'command (append '("pline") coords '("c")))
(setq currobj (ssadd (entlast) currobj))
(setq coords (list 
(list 4800.5625 114.1614) 
(list 4874.585 114.4114) 
(list 4874.585 114.5884) 
(list 4800.5625 114.2384)))
(apply 'command (append '("pline") coords '("c")))
(setq currobj (ssadd (entlast) currobj))
(setq coords (list 
(list 4800.5625 114.3814) 
(list 4874.585 114.7314) 
(list 4874.585 114.9084) 
(list 4800.5625 114.4584)))
(apply 'command (append '("pline") coords '("c")))
(setq currobj (ssadd (entlast) currobj))
(setq coords (list 
(list 4800.5625 114.6014) 
(list 4874.585 115.0514) 
(list 4874.585 115.2284) 
(list 4800.5625 114.6784)))
(apply 'command (append '("pline") coords '("c")))
(setq currobj (ssadd (entlast) currobj))
(setq coords (list 
(list 4800.5625 114.8214) 
(list 4874.585 115.3714) 
(list 4874.585 115.5484) 
(list 4800.5625 114.8984)))
(apply 'command (append '("pline") coords '("c")))
(setq currobj (ssadd (entlast) currobj))
(setq coords (list 
(list 4800.5625 115.0414) 
(list 4874.585 115.6914) 
(list 4874.585 115.8684) 
(list 4800.5625 115.1184)))
(apply 'command (append '("pline") coords '("c")))
(setq currobj (ssadd (entlast) currobj))
(setq coords (list 
(list 4799.4375 115.1184) 
(list 4725.415 115.8684) 
(list 4725.415 115.6914) 
(list 4799.4375 115.0414)))
(apply 'command (append '("pline") coords '("c")))
(setq currobj (ssadd (entlast) currobj))
(setq coords (list 
(list 4799.4375 114.8984) 
(list 4725.415 115.5484) 
(list 4725.415 115.3714) 
(list 4799.4375 114.8214)))
(apply 'command (append '("pline") coords '("c")))
(setq currobj (ssadd (entlast) currobj))
(setq coords (list 
(list 4799.4375 114.6784) 
(list 4725.415 115.2284) 
(list 4725.415 115.0514) 
(list 4799.4375 114.6014)))
(apply 'command (append '("pline") coords '("c")))
(setq currobj (ssadd (entlast) currobj))
(setq coords (list 
(list 4799.4375 114.4584) 
(list 4725.415 114.9084) 
(list 4725.415 114.7314) 
(list 4799.4375 114.3814)))
(apply 'command (append '("pline") coords '("c")))
(setq currobj (ssadd (entlast) currobj))
(setq coords (list 
(list 4799.4375 114.2384) 
(list 4725.415 114.5884) 
(list 4725.415 114.4114) 
(list 4799.4375 114.1614)))
(apply 'command (append '("pline") coords '("c")))
(setq currobj (ssadd (entlast) currobj))
(setq coords (list 
(list 4799.4375 114.0184) 
(list 4725.415 114.2684) 
(list 4725.415 114.0914) 
(list 4799.4375 113.9414)))
(apply 'command (append '("pline") coords '("c")))
(setq currobj (ssadd (entlast) currobj))
(setq coords (list 
(list 4799.4375 113.7984) 
(list 4725.415 113.9484) 
(list 4725.415 113.7714) 
(list 4799.4375 113.7214)))
(apply 'command (append '("pline") coords '("c")))
(setq currobj (ssadd (entlast) currobj))
(setq coords (list 
(list 4799.4375 113.5784) 
(list 4725.415 113.6284) 
(list 4725.415 113.4514) 
(list 4799.4375 113.5014)))
(apply 'command (append '("pline") coords '("c")))
(setq currobj (ssadd (entlast) currobj))
(setq coords (list 
(list 4799.4375 113.3584) 
(list 4725.415 113.3084) 
(list 4725.415 113.1314) 
(list 4799.4375 113.2814)))
(apply 'command (append '("pline") coords '("c")))
(setq currobj (ssadd (entlast) currobj))
(setq coords (list 
(list 4799.4375 113.1384) 
(list 4725.415 112.9884) 
(list 4725.415 112.8114) 
(list 4799.4375 113.0614)))
(apply 'command (append '("pline") coords '("c")))
(setq currobj (ssadd (entlast) currobj))
(setq coords (list 
(list 4799.4375 112.9184) 
(list 4725.415 112.6684) 
(list 4725.415 112.4914) 
(list 4799.4375 112.8414)))
(apply 'command (append '("pline") coords '("c")))
(setq currobj (ssadd (entlast) currobj))
(setq coords (list 
(list 4799.4375 112.6984) 
(list 4725.415 112.3484) 
(list 4725.415 112.1714) 
(list 4799.4375 112.6214)))
(apply 'command (append '("pline") coords '("c")))
(setq currobj (ssadd (entlast) currobj))
(setq coords (list 
(list 4799.4375 112.4784) 
(list 4725.415 112.0284) 
(list 4725.415 111.8514) 
(list 4799.4375 112.4014)))
(apply 'command (append '("pline") coords '("c")))
(setq currobj (ssadd (entlast) currobj))
(setq coords (list 
(list 4799.4375 112.2584) 
(list 4725.415 111.7084) 
(list 4725.415 111.5314) 
(list 4799.4375 112.1814)))
(apply 'command (append '("pline") coords '("c")))
(setq currobj (ssadd (entlast) currobj))
(setq coords (list 
(list 4799.4375 112.0384) 
(list 4725.415 111.3884) 
(list 4725.415 111.2114) 
(list 4799.4375 111.9614)))
(apply 'command (append '("pline") coords '("c")))
(setq currobj (ssadd (entlast) currobj))
(command "_layer" "set" "nitride" "")
(command "_layer" "set" "text" "")
(command "_circle" "4799.0625,100.8184" "0.075")
(command "_circle" "4799.0625,101.1184" "0.075")
(command "_circle" "4799.0625,101.4184" "0.075")
(command "_circle" "4799.0625,101.7184" "0.075")
(command "_circle" "4799.0625,102.0184" "0.075")
(command "_circle" "4798.7625,100.8184" "0.075")
(command "_circle" "4798.7625,101.1184" "0.075")
(command "_circle" "4798.7625,101.4184" "0.075")
(command "_circle" "4798.7625,101.7184" "0.075")
(command "_circle" "4798.7625,102.0184" "0.075")
(command "_circle" "4798.4625,100.8184" "0.075")
(command "_circle" "4798.4625,101.1184" "0.075")
(command "_circle" "4798.4625,101.4184" "0.075")
(command "_circle" "4798.4625,101.7184" "0.075")
(command "_circle" "4798.4625,102.0184" "0.075")
(command "_circle" "4798.1625,100.8184" "0.075")
(command "_circle" "4798.1625,101.1184" "0.075")
(command "_circle" "4798.1625,101.4184" "0.075")
(command "_circle" "4798.1625,101.7184" "0.075")
(command "_circle" "4798.1625,102.0184" "0.075")
(command "_circle" "4797.8625,100.8184" "0.075")
(command "_circle" "4797.8625,101.1184" "0.075")
(command "_circle" "4797.8625,101.4184" "0.075")
(command "_circle" "4797.8625,101.7184" "0.075")
(command "_circle" "4797.8625,102.0184" "0.075")
(command "_layer" "set" "nitride" "")
(setq coords (list 
(list 4800.2625 126.2614) 
(list 4800.2625 241.9061) 
(list 4799.7375 241.9061) 
(list 4799.7375 126.2614)))
(apply 'command (append '("pline") coords '("c")))
(setq currobj (ssadd (entlast) currobj))
(command "_layer" "set" "prebias" "")
(command "_rectangle" "4799.7375,126.2614" "4800.2625,241.9061")
(setq currobj (ssadd (entlast) currobj))
(command "_layer" "set" "nitride" "")
(setq coords (list 
(list 4800.2625 241.9061) 
(list 4800.5625 251.9061) 
(list 4800.5625 251.9061) 
(list 4800.5625 252.9061) 
(list 4874.585 252.1561) 
(list 4874.585 257.0991) 
(list 4800.5625 256.3491) 
(list 4800.5625 257.3491) 
(list 4800.5625 257.3491) 
(list 4800.2625 267.3491) 
(list 4799.7375 267.3491) 
(list 4799.4375 257.3491) 
(list 4799.4375 257.3491) 
(list 4799.4375 256.3491) 
(list 4725.415 257.0991) 
(list 4725.415 252.1561) 
(list 4799.4375 252.9061) 
(list 4799.4375 251.9061) 
(list 4799.4375 251.9061) 
(list 4799.7375 241.9061)))
(apply 'command (append '("pline") coords '("c")))
(setq currobj (ssadd (entlast) currobj))
(command "_layer" "set" "prebias" "")
(setq coords (list 
(list 4799.4375 241.9061) 
(list 4799.4375 252.9061) 
(list 4725.415 252.1561) 
(list 4725.415 257.0991) 
(list 4799.4375 256.3491) 
(list 4799.4375 267.3491) 
(list 4800.5625 267.3491) 
(list 4800.5625 256.3491) 
(list 4874.585 257.0991) 
(list 4874.585 252.1561) 
(list 4800.5625 252.9061) 
(list 4800.5625 241.9061)))
(apply 'command (append '("pline") coords '("c")))
(setq currobj (ssadd (entlast) currobj))
(command "_layer" "set" "nitride" "")
(command "_layer" "set" "fda1" "")
(setq coords (list 
(list 4800.5625 253.0491) 
(list 4874.585 252.2991) 
(list 4874.585 252.4761) 
(list 4800.5625 253.1261)))
(apply 'command (append '("pline") coords '("c")))
(setq currobj (ssadd (entlast) currobj))
(setq coords (list 
(list 4800.5625 253.2691) 
(list 4874.585 252.6191) 
(list 4874.585 252.7961) 
(list 4800.5625 253.3461)))
(apply 'command (append '("pline") coords '("c")))
(setq currobj (ssadd (entlast) currobj))
(setq coords (list 
(list 4800.5625 253.4891) 
(list 4874.585 252.9391) 
(list 4874.585 253.1161) 
(list 4800.5625 253.5661)))
(apply 'command (append '("pline") coords '("c")))
(setq currobj (ssadd (entlast) currobj))
(setq coords (list 
(list 4800.5625 253.7091) 
(list 4874.585 253.2591) 
(list 4874.585 253.4361) 
(list 4800.5625 253.7861)))
(apply 'command (append '("pline") coords '("c")))
(setq currobj (ssadd (entlast) currobj))
(setq coords (list 
(list 4800.5625 253.9291) 
(list 4874.585 253.5791) 
(list 4874.585 253.7561) 
(list 4800.5625 254.0061)))
(apply 'command (append '("pline") coords '("c")))
(setq currobj (ssadd (entlast) currobj))
(setq coords (list 
(list 4800.5625 254.1491) 
(list 4874.585 253.8991) 
(list 4874.585 254.0761) 
(list 4800.5625 254.2261)))
(apply 'command (append '("pline") coords '("c")))
(setq currobj (ssadd (entlast) currobj))
(setq coords (list 
(list 4800.5625 254.3691) 
(list 4874.585 254.2191) 
(list 4874.585 254.3961) 
(list 4800.5625 254.4461)))
(apply 'command (append '("pline") coords '("c")))
(setq currobj (ssadd (entlast) currobj))
(setq coords (list 
(list 4800.5625 254.5891) 
(list 4874.585 254.5391) 
(list 4874.585 254.7161) 
(list 4800.5625 254.6661)))
(apply 'command (append '("pline") coords '("c")))
(setq currobj (ssadd (entlast) currobj))
(setq coords (list 
(list 4800.5625 254.8091) 
(list 4874.585 254.8591) 
(list 4874.585 255.0361) 
(list 4800.5625 254.8861)))
(apply 'command (append '("pline") coords '("c")))
(setq currobj (ssadd (entlast) currobj))
(setq coords (list 
(list 4800.5625 255.0291) 
(list 4874.585 255.1791) 
(list 4874.585 255.3561) 
(list 4800.5625 255.1061)))
(apply 'command (append '("pline") coords '("c")))
(setq currobj (ssadd (entlast) currobj))
(setq coords (list 
(list 4800.5625 255.2491) 
(list 4874.585 255.4991) 
(list 4874.585 255.6761) 
(list 4800.5625 255.3261)))
(apply 'command (append '("pline") coords '("c")))
(setq currobj (ssadd (entlast) currobj))
(setq coords (list 
(list 4800.5625 255.4691) 
(list 4874.585 255.8191) 
(list 4874.585 255.9961) 
(list 4800.5625 255.5461)))
(apply 'command (append '("pline") coords '("c")))
(setq currobj (ssadd (entlast) currobj))
(setq coords (list 
(list 4800.5625 255.6891) 
(list 4874.585 256.1391) 
(list 4874.585 256.3161) 
(list 4800.5625 255.7661)))
(apply 'command (append '("pline") coords '("c")))
(setq currobj (ssadd (entlast) currobj))
(setq coords (list 
(list 4800.5625 255.9091) 
(list 4874.585 256.4591) 
(list 4874.585 256.6361) 
(list 4800.5625 255.9861)))
(apply 'command (append '("pline") coords '("c")))
(setq currobj (ssadd (entlast) currobj))
(setq coords (list 
(list 4800.5625 256.1291) 
(list 4874.585 256.7791) 
(list 4874.585 256.9561) 
(list 4800.5625 256.2061)))
(apply 'command (append '("pline") coords '("c")))
(setq currobj (ssadd (entlast) currobj))
(setq coords (list 
(list 4799.4375 256.2061) 
(list 4725.415 256.9561) 
(list 4725.415 256.7791) 
(list 4799.4375 256.1291)))
(apply 'command (append '("pline") coords '("c")))
(setq currobj (ssadd (entlast) currobj))
(setq coords (list 
(list 4799.4375 255.9861) 
(list 4725.415 256.6361) 
(list 4725.415 256.4591) 
(list 4799.4375 255.9091)))
(apply 'command (append '("pline") coords '("c")))
(setq currobj (ssadd (entlast) currobj))
(setq coords (list 
(list 4799.4375 255.7661) 
(list 4725.415 256.3161) 
(list 4725.415 256.1391) 
(list 4799.4375 255.6891)))
(apply 'command (append '("pline") coords '("c")))
(setq currobj (ssadd (entlast) currobj))
(setq coords (list 
(list 4799.4375 255.5461) 
(list 4725.415 255.9961) 
(list 4725.415 255.8191) 
(list 4799.4375 255.4691)))
(apply 'command (append '("pline") coords '("c")))
(setq currobj (ssadd (entlast) currobj))
(setq coords (list 
(list 4799.4375 255.3261) 
(list 4725.415 255.6761) 
(list 4725.415 255.4991) 
(list 4799.4375 255.2491)))
(apply 'command (append '("pline") coords '("c")))
(setq currobj (ssadd (entlast) currobj))
(setq coords (list 
(list 4799.4375 255.1061) 
(list 4725.415 255.3561) 
(list 4725.415 255.1791) 
(list 4799.4375 255.0291)))
(apply 'command (append '("pline") coords '("c")))
(setq currobj (ssadd (entlast) currobj))
(setq coords (list 
(list 4799.4375 254.8861) 
(list 4725.415 255.0361) 
(list 4725.415 254.8591) 
(list 4799.4375 254.8091)))
(apply 'command (append '("pline") coords '("c")))
(setq currobj (ssadd (entlast) currobj))
(setq coords (list 
(list 4799.4375 254.6661) 
(list 4725.415 254.7161) 
(list 4725.415 254.5391) 
(list 4799.4375 254.5891)))
(apply 'command (append '("pline") coords '("c")))
(setq currobj (ssadd (entlast) currobj))
(setq coords (list 
(list 4799.4375 254.4461) 
(list 4725.415 254.3961) 
(list 4725.415 254.2191) 
(list 4799.4375 254.3691)))
(apply 'command (append '("pline") coords '("c")))
(setq currobj (ssadd (entlast) currobj))
(setq coords (list 
(list 4799.4375 254.2261) 
(list 4725.415 254.0761) 
(list 4725.415 253.8991) 
(list 4799.4375 254.1491)))
(apply 'command (append '("pline") coords '("c")))
(setq currobj (ssadd (entlast) currobj))
(setq coords (list 
(list 4799.4375 254.0061) 
(list 4725.415 253.7561) 
(list 4725.415 253.5791) 
(list 4799.4375 253.9291)))
(apply 'command (append '("pline") coords '("c")))
(setq currobj (ssadd (entlast) currobj))
(setq coords (list 
(list 4799.4375 253.7861) 
(list 4725.415 253.4361) 
(list 4725.415 253.2591) 
(list 4799.4375 253.7091)))
(apply 'command (append '("pline") coords '("c")))
(setq currobj (ssadd (entlast) currobj))
(setq coords (list 
(list 4799.4375 253.5661) 
(list 4725.415 253.1161) 
(list 4725.415 252.9391) 
(list 4799.4375 253.4891)))
(apply 'command (append '("pline") coords '("c")))
(setq currobj (ssadd (entlast) currobj))
(setq coords (list 
(list 4799.4375 253.3461) 
(list 4725.415 252.7961) 
(list 4725.415 252.6191) 
(list 4799.4375 253.2691)))
(apply 'command (append '("pline") coords '("c")))
(setq currobj (ssadd (entlast) currobj))
(setq coords (list 
(list 4799.4375 253.1261) 
(list 4725.415 252.4761) 
(list 4725.415 252.2991) 
(list 4799.4375 253.0491)))
(apply 'command (append '("pline") coords '("c")))
(setq currobj (ssadd (entlast) currobj))
(command "_layer" "set" "nitride" "")
(command "_layer" "set" "text" "")
(command "_circle" "4799.0625,241.9061" "0.075")
(command "_circle" "4799.0625,242.2061" "0.075")
(command "_circle" "4799.0625,242.5061" "0.075")
(command "_circle" "4799.0625,242.8061" "0.075")
(command "_circle" "4799.0625,243.1061" "0.075")
(command "_circle" "4798.7625,241.9061" "0.075")
(command "_circle" "4798.7625,242.2061" "0.075")
(command "_circle" "4798.7625,242.5061" "0.075")
(command "_circle" "4798.7625,242.8061" "0.075")
(command "_circle" "4798.7625,243.1061" "0.075")
(command "_circle" "4798.4625,241.9061" "0.075")
(command "_circle" "4798.4625,242.2061" "0.075")
(command "_circle" "4798.4625,242.5061" "0.075")
(command "_circle" "4798.4625,242.8061" "0.075")
(command "_circle" "4798.4625,243.1061" "0.075")
(command "_circle" "4798.1625,241.9061" "0.075")
(command "_circle" "4798.1625,242.2061" "0.075")
(command "_circle" "4798.1625,242.5061" "0.075")
(command "_circle" "4798.1625,242.8061" "0.075")
(command "_circle" "4798.1625,243.1061" "0.075")
(command "_circle" "4797.8625,241.9061" "0.075")
(command "_circle" "4797.8625,242.2061" "0.075")
(command "_circle" "4797.8625,242.5061" "0.075")
(command "_circle" "4797.8625,242.8061" "0.075")
(command "_circle" "4797.8625,243.1061" "0.075")
(command "_layer" "set" "nitride" "")
(setq coords (list 
(list 4800.2625 267.3491) 
(list 4800.2625 382.9939) 
(list 4799.7375 382.9939) 
(list 4799.7375 267.3491)))
(apply 'command (append '("pline") coords '("c")))
(setq currobj (ssadd (entlast) currobj))
(command "_layer" "set" "prebias" "")
(command "_rectangle" "4799.7375,267.3491" "4800.2625,382.9939")
(setq currobj (ssadd (entlast) currobj))
(command "_layer" "set" "nitride" "")
(setq coords (list 
(list 4800.2625 382.9939) 
(list 4800.5625 392.9939) 
(list 4800.5625 392.9939) 
(list 4800.5625 393.9939) 
(list 4874.585 393.2439) 
(list 4874.585 398.1869) 
(list 4800.5625 397.4369) 
(list 4800.5625 398.4369) 
(list 4800.5625 398.4369) 
(list 4800.2625 408.4369) 
(list 4799.7375 408.4369) 
(list 4799.4375 398.4369) 
(list 4799.4375 398.4369) 
(list 4799.4375 397.4369) 
(list 4725.415 398.1869) 
(list 4725.415 393.2439) 
(list 4799.4375 393.9939) 
(list 4799.4375 392.9939) 
(list 4799.4375 392.9939) 
(list 4799.7375 382.9939)))
(apply 'command (append '("pline") coords '("c")))
(setq currobj (ssadd (entlast) currobj))
(command "_layer" "set" "prebias" "")
(setq coords (list 
(list 4799.4375 382.9939) 
(list 4799.4375 393.9939) 
(list 4725.415 393.2439) 
(list 4725.415 398.1869) 
(list 4799.4375 397.4369) 
(list 4799.4375 408.4369) 
(list 4800.5625 408.4369) 
(list 4800.5625 397.4369) 
(list 4874.585 398.1869) 
(list 4874.585 393.2439) 
(list 4800.5625 393.9939) 
(list 4800.5625 382.9939)))
(apply 'command (append '("pline") coords '("c")))
(setq currobj (ssadd (entlast) currobj))
(command "_layer" "set" "nitride" "")
(command "_layer" "set" "fda1" "")
(setq coords (list 
(list 4800.5625 394.1369) 
(list 4874.585 393.3869) 
(list 4874.585 393.5639) 
(list 4800.5625 394.2139)))
(apply 'command (append '("pline") coords '("c")))
(setq currobj (ssadd (entlast) currobj))
(setq coords (list 
(list 4800.5625 394.3569) 
(list 4874.585 393.7069) 
(list 4874.585 393.8839) 
(list 4800.5625 394.4339)))
(apply 'command (append '("pline") coords '("c")))
(setq currobj (ssadd (entlast) currobj))
(setq coords (list 
(list 4800.5625 394.5769) 
(list 4874.585 394.0269) 
(list 4874.585 394.2039) 
(list 4800.5625 394.6539)))
(apply 'command (append '("pline") coords '("c")))
(setq currobj (ssadd (entlast) currobj))
(setq coords (list 
(list 4800.5625 394.7969) 
(list 4874.585 394.3469) 
(list 4874.585 394.5239) 
(list 4800.5625 394.8739)))
(apply 'command (append '("pline") coords '("c")))
(setq currobj (ssadd (entlast) currobj))
(setq coords (list 
(list 4800.5625 395.0169) 
(list 4874.585 394.6669) 
(list 4874.585 394.8439) 
(list 4800.5625 395.0939)))
(apply 'command (append '("pline") coords '("c")))
(setq currobj (ssadd (entlast) currobj))
(setq coords (list 
(list 4800.5625 395.2369) 
(list 4874.585 394.9869) 
(list 4874.585 395.1639) 
(list 4800.5625 395.3139)))
(apply 'command (append '("pline") coords '("c")))
(setq currobj (ssadd (entlast) currobj))
(setq coords (list 
(list 4800.5625 395.4569) 
(list 4874.585 395.3069) 
(list 4874.585 395.4839) 
(list 4800.5625 395.5339)))
(apply 'command (append '("pline") coords '("c")))
(setq currobj (ssadd (entlast) currobj))
(setq coords (list 
(list 4800.5625 395.6769) 
(list 4874.585 395.6269) 
(list 4874.585 395.8039) 
(list 4800.5625 395.7539)))
(apply 'command (append '("pline") coords '("c")))
(setq currobj (ssadd (entlast) currobj))
(setq coords (list 
(list 4800.5625 395.8969) 
(list 4874.585 395.9469) 
(list 4874.585 396.1239) 
(list 4800.5625 395.9739)))
(apply 'command (append '("pline") coords '("c")))
(setq currobj (ssadd (entlast) currobj))
(setq coords (list 
(list 4800.5625 396.1169) 
(list 4874.585 396.2669) 
(list 4874.585 396.4439) 
(list 4800.5625 396.1939)))
(apply 'command (append '("pline") coords '("c")))
(setq currobj (ssadd (entlast) currobj))
(setq coords (list 
(list 4800.5625 396.3369) 
(list 4874.585 396.5869) 
(list 4874.585 396.7639) 
(list 4800.5625 396.4139)))
(apply 'command (append '("pline") coords '("c")))
(setq currobj (ssadd (entlast) currobj))
(setq coords (list 
(list 4800.5625 396.5569) 
(list 4874.585 396.9069) 
(list 4874.585 397.0839) 
(list 4800.5625 396.6339)))
(apply 'command (append '("pline") coords '("c")))
(setq currobj (ssadd (entlast) currobj))
(setq coords (list 
(list 4800.5625 396.7769) 
(list 4874.585 397.2269) 
(list 4874.585 397.4039) 
(list 4800.5625 396.8539)))
(apply 'command (append '("pline") coords '("c")))
(setq currobj (ssadd (entlast) currobj))
(setq coords (list 
(list 4800.5625 396.9969) 
(list 4874.585 397.5469) 
(list 4874.585 397.7239) 
(list 4800.5625 397.0739)))
(apply 'command (append '("pline") coords '("c")))
(setq currobj (ssadd (entlast) currobj))
(setq coords (list 
(list 4800.5625 397.2169) 
(list 4874.585 397.8669) 
(list 4874.585 398.0439) 
(list 4800.5625 397.2939)))
(apply 'command (append '("pline") coords '("c")))
(setq currobj (ssadd (entlast) currobj))
(setq coords (list 
(list 4799.4375 397.2939) 
(list 4725.415 398.0439) 
(list 4725.415 397.8669) 
(list 4799.4375 397.2169)))
(apply 'command (append '("pline") coords '("c")))
(setq currobj (ssadd (entlast) currobj))
(setq coords (list 
(list 4799.4375 397.0739) 
(list 4725.415 397.7239) 
(list 4725.415 397.5469) 
(list 4799.4375 396.9969)))
(apply 'command (append '("pline") coords '("c")))
(setq currobj (ssadd (entlast) currobj))
(setq coords (list 
(list 4799.4375 396.8539) 
(list 4725.415 397.4039) 
(list 4725.415 397.2269) 
(list 4799.4375 396.7769)))
(apply 'command (append '("pline") coords '("c")))
(setq currobj (ssadd (entlast) currobj))
(setq coords (list 
(list 4799.4375 396.6339) 
(list 4725.415 397.0839) 
(list 4725.415 396.9069) 
(list 4799.4375 396.5569)))
(apply 'command (append '("pline") coords '("c")))
(setq currobj (ssadd (entlast) currobj))
(setq coords (list 
(list 4799.4375 396.4139) 
(list 4725.415 396.7639) 
(list 4725.415 396.5869) 
(list 4799.4375 396.3369)))
(apply 'command (append '("pline") coords '("c")))
(setq currobj (ssadd (entlast) currobj))
(setq coords (list 
(list 4799.4375 396.1939) 
(list 4725.415 396.4439) 
(list 4725.415 396.2669) 
(list 4799.4375 396.1169)))
(apply 'command (append '("pline") coords '("c")))
(setq currobj (ssadd (entlast) currobj))
(setq coords (list 
(list 4799.4375 395.9739) 
(list 4725.415 396.1239) 
(list 4725.415 395.9469) 
(list 4799.4375 395.8969)))
(apply 'command (append '("pline") coords '("c")))
(setq currobj (ssadd (entlast) currobj))
(setq coords (list 
(list 4799.4375 395.7539) 
(list 4725.415 395.8039) 
(list 4725.415 395.6269) 
(list 4799.4375 395.6769)))
(apply 'command (append '("pline") coords '("c")))
(setq currobj (ssadd (entlast) currobj))
(setq coords (list 
(list 4799.4375 395.5339) 
(list 4725.415 395.4839) 
(list 4725.415 395.3069) 
(list 4799.4375 395.4569)))
(apply 'command (append '("pline") coords '("c")))
(setq currobj (ssadd (entlast) currobj))
(setq coords (list 
(list 4799.4375 395.3139) 
(list 4725.415 395.1639) 
(list 4725.415 394.9869) 
(list 4799.4375 395.2369)))
(apply 'command (append '("pline") coords '("c")))
(setq currobj (ssadd (entlast) currobj))
(setq coords (list 
(list 4799.4375 395.0939) 
(list 4725.415 394.8439) 
(list 4725.415 394.6669) 
(list 4799.4375 395.0169)))
(apply 'command (append '("pline") coords '("c")))
(setq currobj (ssadd (entlast) currobj))
(setq coords (list 
(list 4799.4375 394.8739) 
(list 4725.415 394.5239) 
(list 4725.415 394.3469) 
(list 4799.4375 394.7969)))
(apply 'command (append '("pline") coords '("c")))
(setq currobj (ssadd (entlast) currobj))
(setq coords (list 
(list 4799.4375 394.6539) 
(list 4725.415 394.2039) 
(list 4725.415 394.0269) 
(list 4799.4375 394.5769)))
(apply 'command (append '("pline") coords '("c")))
(setq currobj (ssadd (entlast) currobj))
(setq coords (list 
(list 4799.4375 394.4339) 
(list 4725.415 393.8839) 
(list 4725.415 393.7069) 
(list 4799.4375 394.3569)))
(apply 'command (append '("pline") coords '("c")))
(setq currobj (ssadd (entlast) currobj))
(setq coords (list 
(list 4799.4375 394.2139) 
(list 4725.415 393.5639) 
(list 4725.415 393.3869) 
(list 4799.4375 394.1369)))
(apply 'command (append '("pline") coords '("c")))
(setq currobj (ssadd (entlast) currobj))
(command "_layer" "set" "nitride" "")
(command "_layer" "set" "text" "")
(command "_circle" "4799.0625,382.9939" "0.075")
(command "_circle" "4799.0625,383.2939" "0.075")
(command "_circle" "4799.0625,383.5939" "0.075")
(command "_circle" "4799.0625,383.8939" "0.075")
(command "_circle" "4799.0625,384.1939" "0.075")
(command "_circle" "4798.7625,382.9939" "0.075")
(command "_circle" "4798.7625,383.2939" "0.075")
(command "_circle" "4798.7625,383.5939" "0.075")
(command "_circle" "4798.7625,383.8939" "0.075")
(command "_circle" "4798.7625,384.1939" "0.075")
(command "_circle" "4798.4625,382.9939" "0.075")
(command "_circle" "4798.4625,383.2939" "0.075")
(command "_circle" "4798.4625,383.5939" "0.075")
(command "_circle" "4798.4625,383.8939" "0.075")
(command "_circle" "4798.4625,384.1939" "0.075")
(command "_circle" "4798.1625,382.9939" "0.075")
(command "_circle" "4798.1625,383.2939" "0.075")
(command "_circle" "4798.1625,383.5939" "0.075")
(command "_circle" "4798.1625,383.8939" "0.075")
(command "_circle" "4798.1625,384.1939" "0.075")
(command "_circle" "4797.8625,382.9939" "0.075")
(command "_circle" "4797.8625,383.2939" "0.075")
(command "_circle" "4797.8625,383.5939" "0.075")
(command "_circle" "4797.8625,383.8939" "0.075")
(command "_circle" "4797.8625,384.1939" "0.075")
(command "_layer" "set" "nitride" "")
(setq coords (list 
(list 4800.2625 408.4369) 
(list 4800.2625 524.0816) 
(list 4799.7375 524.0816) 
(list 4799.7375 408.4369)))
(apply 'command (append '("pline") coords '("c")))
(setq currobj (ssadd (entlast) currobj))
(command "_layer" "set" "prebias" "")
(command "_rectangle" "4799.7375,408.4369" "4800.2625,524.0816")
(setq currobj (ssadd (entlast) currobj))
(command "_layer" "set" "nitride" "")
(setq coords (list 
(list 4800.2625 524.0816) 
(list 4800.5625 534.0816) 
(list 4800.5625 534.0816) 
(list 4800.5625 535.0816) 
(list 4874.585 534.3316) 
(list 4874.585 539.2746) 
(list 4800.5625 538.5246) 
(list 4800.5625 539.5246) 
(list 4800.5625 539.5246) 
(list 4800.2625 549.5246) 
(list 4799.7375 549.5246) 
(list 4799.4375 539.5246) 
(list 4799.4375 539.5246) 
(list 4799.4375 538.5246) 
(list 4725.415 539.2746) 
(list 4725.415 534.3316) 
(list 4799.4375 535.0816) 
(list 4799.4375 534.0816) 
(list 4799.4375 534.0816) 
(list 4799.7375 524.0816)))
(apply 'command (append '("pline") coords '("c")))
(setq currobj (ssadd (entlast) currobj))
(command "_layer" "set" "prebias" "")
(setq coords (list 
(list 4799.4375 524.0816) 
(list 4799.4375 535.0816) 
(list 4725.415 534.3316) 
(list 4725.415 539.2746) 
(list 4799.4375 538.5246) 
(list 4799.4375 549.5246) 
(list 4800.5625 549.5246) 
(list 4800.5625 538.5246) 
(list 4874.585 539.2746) 
(list 4874.585 534.3316) 
(list 4800.5625 535.0816) 
(list 4800.5625 524.0816)))
(apply 'command (append '("pline") coords '("c")))
(setq currobj (ssadd (entlast) currobj))
(command "_layer" "set" "nitride" "")
(command "_layer" "set" "fda1" "")
(setq coords (list 
(list 4800.5625 535.2246) 
(list 4874.585 534.4746) 
(list 4874.585 534.6516) 
(list 4800.5625 535.3016)))
(apply 'command (append '("pline") coords '("c")))
(setq currobj (ssadd (entlast) currobj))
(setq coords (list 
(list 4800.5625 535.4446) 
(list 4874.585 534.7946) 
(list 4874.585 534.9716) 
(list 4800.5625 535.5216)))
(apply 'command (append '("pline") coords '("c")))
(setq currobj (ssadd (entlast) currobj))
(setq coords (list 
(list 4800.5625 535.6646) 
(list 4874.585 535.1146) 
(list 4874.585 535.2916) 
(list 4800.5625 535.7416)))
(apply 'command (append '("pline") coords '("c")))
(setq currobj (ssadd (entlast) currobj))
(setq coords (list 
(list 4800.5625 535.8846) 
(list 4874.585 535.4346) 
(list 4874.585 535.6116) 
(list 4800.5625 535.9616)))
(apply 'command (append '("pline") coords '("c")))
(setq currobj (ssadd (entlast) currobj))
(setq coords (list 
(list 4800.5625 536.1046) 
(list 4874.585 535.7546) 
(list 4874.585 535.9316) 
(list 4800.5625 536.1816)))
(apply 'command (append '("pline") coords '("c")))
(setq currobj (ssadd (entlast) currobj))
(setq coords (list 
(list 4800.5625 536.3246) 
(list 4874.585 536.0746) 
(list 4874.585 536.2516) 
(list 4800.5625 536.4016)))
(apply 'command (append '("pline") coords '("c")))
(setq currobj (ssadd (entlast) currobj))
(setq coords (list 
(list 4800.5625 536.5446) 
(list 4874.585 536.3946) 
(list 4874.585 536.5716) 
(list 4800.5625 536.6216)))
(apply 'command (append '("pline") coords '("c")))
(setq currobj (ssadd (entlast) currobj))
(setq coords (list 
(list 4800.5625 536.7646) 
(list 4874.585 536.7146) 
(list 4874.585 536.8916) 
(list 4800.5625 536.8416)))
(apply 'command (append '("pline") coords '("c")))
(setq currobj (ssadd (entlast) currobj))
(setq coords (list 
(list 4800.5625 536.9846) 
(list 4874.585 537.0346) 
(list 4874.585 537.2116) 
(list 4800.5625 537.0616)))
(apply 'command (append '("pline") coords '("c")))
(setq currobj (ssadd (entlast) currobj))
(setq coords (list 
(list 4800.5625 537.2046) 
(list 4874.585 537.3546) 
(list 4874.585 537.5316) 
(list 4800.5625 537.2816)))
(apply 'command (append '("pline") coords '("c")))
(setq currobj (ssadd (entlast) currobj))
(setq coords (list 
(list 4800.5625 537.4246) 
(list 4874.585 537.6746) 
(list 4874.585 537.8516) 
(list 4800.5625 537.5016)))
(apply 'command (append '("pline") coords '("c")))
(setq currobj (ssadd (entlast) currobj))
(setq coords (list 
(list 4800.5625 537.6446) 
(list 4874.585 537.9946) 
(list 4874.585 538.1716) 
(list 4800.5625 537.7216)))
(apply 'command (append '("pline") coords '("c")))
(setq currobj (ssadd (entlast) currobj))
(setq coords (list 
(list 4800.5625 537.8646) 
(list 4874.585 538.3146) 
(list 4874.585 538.4916) 
(list 4800.5625 537.9416)))
(apply 'command (append '("pline") coords '("c")))
(setq currobj (ssadd (entlast) currobj))
(setq coords (list 
(list 4800.5625 538.0846) 
(list 4874.585 538.6346) 
(list 4874.585 538.8116) 
(list 4800.5625 538.1616)))
(apply 'command (append '("pline") coords '("c")))
(setq currobj (ssadd (entlast) currobj))
(setq coords (list 
(list 4800.5625 538.3046) 
(list 4874.585 538.9546) 
(list 4874.585 539.1316) 
(list 4800.5625 538.3816)))
(apply 'command (append '("pline") coords '("c")))
(setq currobj (ssadd (entlast) currobj))
(setq coords (list 
(list 4799.4375 538.3816) 
(list 4725.415 539.1316) 
(list 4725.415 538.9546) 
(list 4799.4375 538.3046)))
(apply 'command (append '("pline") coords '("c")))
(setq currobj (ssadd (entlast) currobj))
(setq coords (list 
(list 4799.4375 538.1616) 
(list 4725.415 538.8116) 
(list 4725.415 538.6346) 
(list 4799.4375 538.0846)))
(apply 'command (append '("pline") coords '("c")))
(setq currobj (ssadd (entlast) currobj))
(setq coords (list 
(list 4799.4375 537.9416) 
(list 4725.415 538.4916) 
(list 4725.415 538.3146) 
(list 4799.4375 537.8646)))
(apply 'command (append '("pline") coords '("c")))
(setq currobj (ssadd (entlast) currobj))
(setq coords (list 
(list 4799.4375 537.7216) 
(list 4725.415 538.1716) 
(list 4725.415 537.9946) 
(list 4799.4375 537.6446)))
(apply 'command (append '("pline") coords '("c")))
(setq currobj (ssadd (entlast) currobj))
(setq coords (list 
(list 4799.4375 537.5016) 
(list 4725.415 537.8516) 
(list 4725.415 537.6746) 
(list 4799.4375 537.4246)))
(apply 'command (append '("pline") coords '("c")))
(setq currobj (ssadd (entlast) currobj))
(setq coords (list 
(list 4799.4375 537.2816) 
(list 4725.415 537.5316) 
(list 4725.415 537.3546) 
(list 4799.4375 537.2046)))
(apply 'command (append '("pline") coords '("c")))
(setq currobj (ssadd (entlast) currobj))
(setq coords (list 
(list 4799.4375 537.0616) 
(list 4725.415 537.2116) 
(list 4725.415 537.0346) 
(list 4799.4375 536.9846)))
(apply 'command (append '("pline") coords '("c")))
(setq currobj (ssadd (entlast) currobj))
(setq coords (list 
(list 4799.4375 536.8416) 
(list 4725.415 536.8916) 
(list 4725.415 536.7146) 
(list 4799.4375 536.7646)))
(apply 'command (append '("pline") coords '("c")))
(setq currobj (ssadd (entlast) currobj))
(setq coords (list 
(list 4799.4375 536.6216) 
(list 4725.415 536.5716) 
(list 4725.415 536.3946) 
(list 4799.4375 536.5446)))
(apply 'command (append '("pline") coords '("c")))
(setq currobj (ssadd (entlast) currobj))
(setq coords (list 
(list 4799.4375 536.4016) 
(list 4725.415 536.2516) 
(list 4725.415 536.0746) 
(list 4799.4375 536.3246)))
(apply 'command (append '("pline") coords '("c")))
(setq currobj (ssadd (entlast) currobj))
(setq coords (list 
(list 4799.4375 536.1816) 
(list 4725.415 535.9316) 
(list 4725.415 535.7546) 
(list 4799.4375 536.1046)))
(apply 'command (append '("pline") coords '("c")))
(setq currobj (ssadd (entlast) currobj))
(setq coords (list 
(list 4799.4375 535.9616) 
(list 4725.415 535.6116) 
(list 4725.415 535.4346) 
(list 4799.4375 535.8846)))
(apply 'command (append '("pline") coords '("c")))
(setq currobj (ssadd (entlast) currobj))
(setq coords (list 
(list 4799.4375 535.7416) 
(list 4725.415 535.2916) 
(list 4725.415 535.1146) 
(list 4799.4375 535.6646)))
(apply 'command (append '("pline") coords '("c")))
(setq currobj (ssadd (entlast) currobj))
(setq coords (list 
(list 4799.4375 535.5216) 
(list 4725.415 534.9716) 
(list 4725.415 534.7946) 
(list 4799.4375 535.4446)))
(apply 'command (append '("pline") coords '("c")))
(setq currobj (ssadd (entlast) currobj))
(setq coords (list 
(list 4799.4375 535.3016) 
(list 4725.415 534.6516) 
(list 4725.415 534.4746) 
(list 4799.4375 535.2246)))
(apply 'command (append '("pline") coords '("c")))
(setq currobj (ssadd (entlast) currobj))
(command "_layer" "set" "nitride" "")
(command "_layer" "set" "text" "")
(command "_circle" "4799.0625,524.0816" "0.075")
(command "_circle" "4799.0625,524.3816" "0.075")
(command "_circle" "4799.0625,524.6816" "0.075")
(command "_circle" "4799.0625,524.9816" "0.075")
(command "_circle" "4799.0625,525.2816" "0.075")
(command "_circle" "4798.7625,524.0816" "0.075")
(command "_circle" "4798.7625,524.3816" "0.075")
(command "_circle" "4798.7625,524.6816" "0.075")
(command "_circle" "4798.7625,524.9816" "0.075")
(command "_circle" "4798.7625,525.2816" "0.075")
(command "_circle" "4798.4625,524.0816" "0.075")
(command "_circle" "4798.4625,524.3816" "0.075")
(command "_circle" "4798.4625,524.6816" "0.075")
(command "_circle" "4798.4625,524.9816" "0.075")
(command "_circle" "4798.4625,525.2816" "0.075")
(command "_circle" "4798.1625,524.0816" "0.075")
(command "_circle" "4798.1625,524.3816" "0.075")
(command "_circle" "4798.1625,524.6816" "0.075")
(command "_circle" "4798.1625,524.9816" "0.075")
(command "_circle" "4798.1625,525.2816" "0.075")
(command "_circle" "4797.8625,524.0816" "0.075")
(command "_circle" "4797.8625,524.3816" "0.075")
(command "_circle" "4797.8625,524.6816" "0.075")
(command "_circle" "4797.8625,524.9816" "0.075")
(command "_circle" "4797.8625,525.2816" "0.075")
(command "_layer" "set" "nitride" "")
(setq coords (list 
(list 4800.2625 549.5246) 
(list 4800.2625 665.1693) 
(list 4799.7375 665.1693) 
(list 4799.7375 549.5246)))
(apply 'command (append '("pline") coords '("c")))
(setq currobj (ssadd (entlast) currobj))
(command "_layer" "set" "prebias" "")
(command "_rectangle" "4799.7375,549.5246" "4800.2625,665.1693")
(setq currobj (ssadd (entlast) currobj))
(command "_layer" "set" "nitride" "")
(setq coords (list 
(list 4800.2625 665.1693) 
(list 4800.5625 675.1693) 
(list 4800.5625 675.1693) 
(list 4800.5625 676.1693) 
(list 4874.585 675.4193) 
(list 4874.585 680.3623) 
(list 4800.5625 679.6123) 
(list 4800.5625 680.6123) 
(list 4800.5625 680.6123) 
(list 4800.2625 690.6123) 
(list 4799.7375 690.6123) 
(list 4799.4375 680.6123) 
(list 4799.4375 680.6123) 
(list 4799.4375 679.6123) 
(list 4725.415 680.3623) 
(list 4725.415 675.4193) 
(list 4799.4375 676.1693) 
(list 4799.4375 675.1693) 
(list 4799.4375 675.1693) 
(list 4799.7375 665.1693)))
(apply 'command (append '("pline") coords '("c")))
(setq currobj (ssadd (entlast) currobj))
(command "_layer" "set" "prebias" "")
(setq coords (list 
(list 4799.4375 665.1693) 
(list 4799.4375 676.1693) 
(list 4725.415 675.4193) 
(list 4725.415 680.3623) 
(list 4799.4375 679.6123) 
(list 4799.4375 690.6123) 
(list 4800.5625 690.6123) 
(list 4800.5625 679.6123) 
(list 4874.585 680.3623) 
(list 4874.585 675.4193) 
(list 4800.5625 676.1693) 
(list 4800.5625 665.1693)))
(apply 'command (append '("pline") coords '("c")))
(setq currobj (ssadd (entlast) currobj))
(command "_layer" "set" "nitride" "")
(command "_layer" "set" "fda1" "")
(setq coords (list 
(list 4800.5625 676.3123) 
(list 4874.585 675.5623) 
(list 4874.585 675.7393) 
(list 4800.5625 676.3893)))
(apply 'command (append '("pline") coords '("c")))
(setq currobj (ssadd (entlast) currobj))
(setq coords (list 
(list 4800.5625 676.5323) 
(list 4874.585 675.8823) 
(list 4874.585 676.0593) 
(list 4800.5625 676.6093)))
(apply 'command (append '("pline") coords '("c")))
(setq currobj (ssadd (entlast) currobj))
(setq coords (list 
(list 4800.5625 676.7523) 
(list 4874.585 676.2023) 
(list 4874.585 676.3793) 
(list 4800.5625 676.8293)))
(apply 'command (append '("pline") coords '("c")))
(setq currobj (ssadd (entlast) currobj))
(setq coords (list 
(list 4800.5625 676.9723) 
(list 4874.585 676.5223) 
(list 4874.585 676.6993) 
(list 4800.5625 677.0493)))
(apply 'command (append '("pline") coords '("c")))
(setq currobj (ssadd (entlast) currobj))
(setq coords (list 
(list 4800.5625 677.1923) 
(list 4874.585 676.8423) 
(list 4874.585 677.0193) 
(list 4800.5625 677.2693)))
(apply 'command (append '("pline") coords '("c")))
(setq currobj (ssadd (entlast) currobj))
(setq coords (list 
(list 4800.5625 677.4123) 
(list 4874.585 677.1623) 
(list 4874.585 677.3393) 
(list 4800.5625 677.4893)))
(apply 'command (append '("pline") coords '("c")))
(setq currobj (ssadd (entlast) currobj))
(setq coords (list 
(list 4800.5625 677.6323) 
(list 4874.585 677.4823) 
(list 4874.585 677.6593) 
(list 4800.5625 677.7093)))
(apply 'command (append '("pline") coords '("c")))
(setq currobj (ssadd (entlast) currobj))
(setq coords (list 
(list 4800.5625 677.8523) 
(list 4874.585 677.8023) 
(list 4874.585 677.9793) 
(list 4800.5625 677.9293)))
(apply 'command (append '("pline") coords '("c")))
(setq currobj (ssadd (entlast) currobj))
(setq coords (list 
(list 4800.5625 678.0723) 
(list 4874.585 678.1223) 
(list 4874.585 678.2993) 
(list 4800.5625 678.1493)))
(apply 'command (append '("pline") coords '("c")))
(setq currobj (ssadd (entlast) currobj))
(setq coords (list 
(list 4800.5625 678.2923) 
(list 4874.585 678.4423) 
(list 4874.585 678.6193) 
(list 4800.5625 678.3693)))
(apply 'command (append '("pline") coords '("c")))
(setq currobj (ssadd (entlast) currobj))
(setq coords (list 
(list 4800.5625 678.5123) 
(list 4874.585 678.7623) 
(list 4874.585 678.9393) 
(list 4800.5625 678.5893)))
(apply 'command (append '("pline") coords '("c")))
(setq currobj (ssadd (entlast) currobj))
(setq coords (list 
(list 4800.5625 678.7323) 
(list 4874.585 679.0823) 
(list 4874.585 679.2593) 
(list 4800.5625 678.8093)))
(apply 'command (append '("pline") coords '("c")))
(setq currobj (ssadd (entlast) currobj))
(setq coords (list 
(list 4800.5625 678.9523) 
(list 4874.585 679.4023) 
(list 4874.585 679.5793) 
(list 4800.5625 679.0293)))
(apply 'command (append '("pline") coords '("c")))
(setq currobj (ssadd (entlast) currobj))
(setq coords (list 
(list 4800.5625 679.1723) 
(list 4874.585 679.7223) 
(list 4874.585 679.8993) 
(list 4800.5625 679.2493)))
(apply 'command (append '("pline") coords '("c")))
(setq currobj (ssadd (entlast) currobj))
(setq coords (list 
(list 4800.5625 679.3923) 
(list 4874.585 680.0423) 
(list 4874.585 680.2193) 
(list 4800.5625 679.4693)))
(apply 'command (append '("pline") coords '("c")))
(setq currobj (ssadd (entlast) currobj))
(setq coords (list 
(list 4799.4375 679.4693) 
(list 4725.415 680.2193) 
(list 4725.415 680.0423) 
(list 4799.4375 679.3923)))
(apply 'command (append '("pline") coords '("c")))
(setq currobj (ssadd (entlast) currobj))
(setq coords (list 
(list 4799.4375 679.2493) 
(list 4725.415 679.8993) 
(list 4725.415 679.7223) 
(list 4799.4375 679.1723)))
(apply 'command (append '("pline") coords '("c")))
(setq currobj (ssadd (entlast) currobj))
(setq coords (list 
(list 4799.4375 679.0293) 
(list 4725.415 679.5793) 
(list 4725.415 679.4023) 
(list 4799.4375 678.9523)))
(apply 'command (append '("pline") coords '("c")))
(setq currobj (ssadd (entlast) currobj))
(setq coords (list 
(list 4799.4375 678.8093) 
(list 4725.415 679.2593) 
(list 4725.415 679.0823) 
(list 4799.4375 678.7323)))
(apply 'command (append '("pline") coords '("c")))
(setq currobj (ssadd (entlast) currobj))
(setq coords (list 
(list 4799.4375 678.5893) 
(list 4725.415 678.9393) 
(list 4725.415 678.7623) 
(list 4799.4375 678.5123)))
(apply 'command (append '("pline") coords '("c")))
(setq currobj (ssadd (entlast) currobj))
(setq coords (list 
(list 4799.4375 678.3693) 
(list 4725.415 678.6193) 
(list 4725.415 678.4423) 
(list 4799.4375 678.2923)))
(apply 'command (append '("pline") coords '("c")))
(setq currobj (ssadd (entlast) currobj))
(setq coords (list 
(list 4799.4375 678.1493) 
(list 4725.415 678.2993) 
(list 4725.415 678.1223) 
(list 4799.4375 678.0723)))
(apply 'command (append '("pline") coords '("c")))
(setq currobj (ssadd (entlast) currobj))
(setq coords (list 
(list 4799.4375 677.9293) 
(list 4725.415 677.9793) 
(list 4725.415 677.8023) 
(list 4799.4375 677.8523)))
(apply 'command (append '("pline") coords '("c")))
(setq currobj (ssadd (entlast) currobj))
(setq coords (list 
(list 4799.4375 677.7093) 
(list 4725.415 677.6593) 
(list 4725.415 677.4823) 
(list 4799.4375 677.6323)))
(apply 'command (append '("pline") coords '("c")))
(setq currobj (ssadd (entlast) currobj))
(setq coords (list 
(list 4799.4375 677.4893) 
(list 4725.415 677.3393) 
(list 4725.415 677.1623) 
(list 4799.4375 677.4123)))
(apply 'command (append '("pline") coords '("c")))
(setq currobj (ssadd (entlast) currobj))
(setq coords (list 
(list 4799.4375 677.2693) 
(list 4725.415 677.0193) 
(list 4725.415 676.8423) 
(list 4799.4375 677.1923)))
(apply 'command (append '("pline") coords '("c")))
(setq currobj (ssadd (entlast) currobj))
(setq coords (list 
(list 4799.4375 677.0493) 
(list 4725.415 676.6993) 
(list 4725.415 676.5223) 
(list 4799.4375 676.9723)))
(apply 'command (append '("pline") coords '("c")))
(setq currobj (ssadd (entlast) currobj))
(setq coords (list 
(list 4799.4375 676.8293) 
(list 4725.415 676.3793) 
(list 4725.415 676.2023) 
(list 4799.4375 676.7523)))
(apply 'command (append '("pline") coords '("c")))
(setq currobj (ssadd (entlast) currobj))
(setq coords (list 
(list 4799.4375 676.6093) 
(list 4725.415 676.0593) 
(list 4725.415 675.8823) 
(list 4799.4375 676.5323)))
(apply 'command (append '("pline") coords '("c")))
(setq currobj (ssadd (entlast) currobj))
(setq coords (list 
(list 4799.4375 676.3893) 
(list 4725.415 675.7393) 
(list 4725.415 675.5623) 
(list 4799.4375 676.3123)))
(apply 'command (append '("pline") coords '("c")))
(setq currobj (ssadd (entlast) currobj))
(command "_layer" "set" "nitride" "")
(command "_layer" "set" "text" "")
(command "_circle" "4799.0625,665.1693" "0.075")
(command "_circle" "4799.0625,665.4693" "0.075")
(command "_circle" "4799.0625,665.7693" "0.075")
(command "_circle" "4799.0625,666.0693" "0.075")
(command "_circle" "4799.0625,666.3693" "0.075")
(command "_circle" "4798.7625,665.1693" "0.075")
(command "_circle" "4798.7625,665.4693" "0.075")
(command "_circle" "4798.7625,665.7693" "0.075")
(command "_circle" "4798.7625,666.0693" "0.075")
(command "_circle" "4798.7625,666.3693" "0.075")
(command "_circle" "4798.4625,665.1693" "0.075")
(command "_circle" "4798.4625,665.4693" "0.075")
(command "_circle" "4798.4625,665.7693" "0.075")
(command "_circle" "4798.4625,666.0693" "0.075")
(command "_circle" "4798.4625,666.3693" "0.075")
(command "_circle" "4798.1625,665.1693" "0.075")
(command "_circle" "4798.1625,665.4693" "0.075")
(command "_circle" "4798.1625,665.7693" "0.075")
(command "_circle" "4798.1625,666.0693" "0.075")
(command "_circle" "4798.1625,666.3693" "0.075")
(command "_circle" "4797.8625,665.1693" "0.075")
(command "_circle" "4797.8625,665.4693" "0.075")
(command "_circle" "4797.8625,665.7693" "0.075")
(command "_circle" "4797.8625,666.0693" "0.075")
(command "_circle" "4797.8625,666.3693" "0.075")
(command "_layer" "set" "nitride" "")
(setq coords (list 
(list 4800.2625 690.6123) 
(list 4800.2625 806.257) 
(list 4799.7375 806.257) 
(list 4799.7375 690.6123)))
(apply 'command (append '("pline") coords '("c")))
(setq currobj (ssadd (entlast) currobj))
(command "_layer" "set" "prebias" "")
(command "_rectangle" "4799.7375,690.6123" "4800.2625,806.257")
(setq currobj (ssadd (entlast) currobj))
(command "_layer" "set" "nitride" "")
(setq coords (list 
(list 4800.2625 806.257) 
(list 4800.5625 816.257) 
(list 4800.5625 816.257) 
(list 4800.5625 817.257) 
(list 4874.585 816.507) 
(list 4874.585 821.45) 
(list 4800.5625 820.7) 
(list 4800.5625 821.7) 
(list 4800.5625 821.7) 
(list 4800.2625 831.7) 
(list 4799.7375 831.7) 
(list 4799.4375 821.7) 
(list 4799.4375 821.7) 
(list 4799.4375 820.7) 
(list 4725.415 821.45) 
(list 4725.415 816.507) 
(list 4799.4375 817.257) 
(list 4799.4375 816.257) 
(list 4799.4375 816.257) 
(list 4799.7375 806.257)))
(apply 'command (append '("pline") coords '("c")))
(setq currobj (ssadd (entlast) currobj))
(command "_layer" "set" "prebias" "")
(setq coords (list 
(list 4799.4375 806.257) 
(list 4799.4375 817.257) 
(list 4725.415 816.507) 
(list 4725.415 821.45) 
(list 4799.4375 820.7) 
(list 4799.4375 831.7) 
(list 4800.5625 831.7) 
(list 4800.5625 820.7) 
(list 4874.585 821.45) 
(list 4874.585 816.507) 
(list 4800.5625 817.257) 
(list 4800.5625 806.257)))
(apply 'command (append '("pline") coords '("c")))
(setq currobj (ssadd (entlast) currobj))
(command "_layer" "set" "nitride" "")
(command "_layer" "set" "fda1" "")
(setq coords (list 
(list 4800.5625 817.4) 
(list 4874.585 816.65) 
(list 4874.585 816.827) 
(list 4800.5625 817.477)))
(apply 'command (append '("pline") coords '("c")))
(setq currobj (ssadd (entlast) currobj))
(setq coords (list 
(list 4800.5625 817.62) 
(list 4874.585 816.97) 
(list 4874.585 817.147) 
(list 4800.5625 817.697)))
(apply 'command (append '("pline") coords '("c")))
(setq currobj (ssadd (entlast) currobj))
(setq coords (list 
(list 4800.5625 817.84) 
(list 4874.585 817.29) 
(list 4874.585 817.467) 
(list 4800.5625 817.917)))
(apply 'command (append '("pline") coords '("c")))
(setq currobj (ssadd (entlast) currobj))
(setq coords (list 
(list 4800.5625 818.06) 
(list 4874.585 817.61) 
(list 4874.585 817.787) 
(list 4800.5625 818.137)))
(apply 'command (append '("pline") coords '("c")))
(setq currobj (ssadd (entlast) currobj))
(setq coords (list 
(list 4800.5625 818.28) 
(list 4874.585 817.93) 
(list 4874.585 818.107) 
(list 4800.5625 818.357)))
(apply 'command (append '("pline") coords '("c")))
(setq currobj (ssadd (entlast) currobj))
(setq coords (list 
(list 4800.5625 818.5) 
(list 4874.585 818.25) 
(list 4874.585 818.427) 
(list 4800.5625 818.577)))
(apply 'command (append '("pline") coords '("c")))
(setq currobj (ssadd (entlast) currobj))
(setq coords (list 
(list 4800.5625 818.72) 
(list 4874.585 818.57) 
(list 4874.585 818.747) 
(list 4800.5625 818.797)))
(apply 'command (append '("pline") coords '("c")))
(setq currobj (ssadd (entlast) currobj))
(setq coords (list 
(list 4800.5625 818.94) 
(list 4874.585 818.89) 
(list 4874.585 819.067) 
(list 4800.5625 819.017)))
(apply 'command (append '("pline") coords '("c")))
(setq currobj (ssadd (entlast) currobj))
(setq coords (list 
(list 4800.5625 819.16) 
(list 4874.585 819.21) 
(list 4874.585 819.387) 
(list 4800.5625 819.237)))
(apply 'command (append '("pline") coords '("c")))
(setq currobj (ssadd (entlast) currobj))
(setq coords (list 
(list 4800.5625 819.38) 
(list 4874.585 819.53) 
(list 4874.585 819.707) 
(list 4800.5625 819.457)))
(apply 'command (append '("pline") coords '("c")))
(setq currobj (ssadd (entlast) currobj))
(setq coords (list 
(list 4800.5625 819.6) 
(list 4874.585 819.85) 
(list 4874.585 820.027) 
(list 4800.5625 819.677)))
(apply 'command (append '("pline") coords '("c")))
(setq currobj (ssadd (entlast) currobj))
(setq coords (list 
(list 4800.5625 819.82) 
(list 4874.585 820.17) 
(list 4874.585 820.347) 
(list 4800.5625 819.897)))
(apply 'command (append '("pline") coords '("c")))
(setq currobj (ssadd (entlast) currobj))
(setq coords (list 
(list 4800.5625 820.04) 
(list 4874.585 820.49) 
(list 4874.585 820.667) 
(list 4800.5625 820.117)))
(apply 'command (append '("pline") coords '("c")))
(setq currobj (ssadd (entlast) currobj))
(setq coords (list 
(list 4800.5625 820.26) 
(list 4874.585 820.81) 
(list 4874.585 820.987) 
(list 4800.5625 820.337)))
(apply 'command (append '("pline") coords '("c")))
(setq currobj (ssadd (entlast) currobj))
(setq coords (list 
(list 4800.5625 820.48) 
(list 4874.585 821.13) 
(list 4874.585 821.307) 
(list 4800.5625 820.557)))
(apply 'command (append '("pline") coords '("c")))
(setq currobj (ssadd (entlast) currobj))
(setq coords (list 
(list 4799.4375 820.557) 
(list 4725.415 821.307) 
(list 4725.415 821.13) 
(list 4799.4375 820.48)))
(apply 'command (append '("pline") coords '("c")))
(setq currobj (ssadd (entlast) currobj))
(setq coords (list 
(list 4799.4375 820.337) 
(list 4725.415 820.987) 
(list 4725.415 820.81) 
(list 4799.4375 820.26)))
(apply 'command (append '("pline") coords '("c")))
(setq currobj (ssadd (entlast) currobj))
(setq coords (list 
(list 4799.4375 820.117) 
(list 4725.415 820.667) 
(list 4725.415 820.49) 
(list 4799.4375 820.04)))
(apply 'command (append '("pline") coords '("c")))
(setq currobj (ssadd (entlast) currobj))
(setq coords (list 
(list 4799.4375 819.897) 
(list 4725.415 820.347) 
(list 4725.415 820.17) 
(list 4799.4375 819.82)))
(apply 'command (append '("pline") coords '("c")))
(setq currobj (ssadd (entlast) currobj))
(setq coords (list 
(list 4799.4375 819.677) 
(list 4725.415 820.027) 
(list 4725.415 819.85) 
(list 4799.4375 819.6)))
(apply 'command (append '("pline") coords '("c")))
(setq currobj (ssadd (entlast) currobj))
(setq coords (list 
(list 4799.4375 819.457) 
(list 4725.415 819.707) 
(list 4725.415 819.53) 
(list 4799.4375 819.38)))
(apply 'command (append '("pline") coords '("c")))
(setq currobj (ssadd (entlast) currobj))
(setq coords (list 
(list 4799.4375 819.237) 
(list 4725.415 819.387) 
(list 4725.415 819.21) 
(list 4799.4375 819.16)))
(apply 'command (append '("pline") coords '("c")))
(setq currobj (ssadd (entlast) currobj))
(setq coords (list 
(list 4799.4375 819.017) 
(list 4725.415 819.067) 
(list 4725.415 818.89) 
(list 4799.4375 818.94)))
(apply 'command (append '("pline") coords '("c")))
(setq currobj (ssadd (entlast) currobj))
(setq coords (list 
(list 4799.4375 818.797) 
(list 4725.415 818.747) 
(list 4725.415 818.57) 
(list 4799.4375 818.72)))
(apply 'command (append '("pline") coords '("c")))
(setq currobj (ssadd (entlast) currobj))
(setq coords (list 
(list 4799.4375 818.577) 
(list 4725.415 818.427) 
(list 4725.415 818.25) 
(list 4799.4375 818.5)))
(apply 'command (append '("pline") coords '("c")))
(setq currobj (ssadd (entlast) currobj))
(setq coords (list 
(list 4799.4375 818.357) 
(list 4725.415 818.107) 
(list 4725.415 817.93) 
(list 4799.4375 818.28)))
(apply 'command (append '("pline") coords '("c")))
(setq currobj (ssadd (entlast) currobj))
(setq coords (list 
(list 4799.4375 818.137) 
(list 4725.415 817.787) 
(list 4725.415 817.61) 
(list 4799.4375 818.06)))
(apply 'command (append '("pline") coords '("c")))
(setq currobj (ssadd (entlast) currobj))
(setq coords (list 
(list 4799.4375 817.917) 
(list 4725.415 817.467) 
(list 4725.415 817.29) 
(list 4799.4375 817.84)))
(apply 'command (append '("pline") coords '("c")))
(setq currobj (ssadd (entlast) currobj))
(setq coords (list 
(list 4799.4375 817.697) 
(list 4725.415 817.147) 
(list 4725.415 816.97) 
(list 4799.4375 817.62)))
(apply 'command (append '("pline") coords '("c")))
(setq currobj (ssadd (entlast) currobj))
(setq coords (list 
(list 4799.4375 817.477) 
(list 4725.415 816.827) 
(list 4725.415 816.65) 
(list 4799.4375 817.4)))
(apply 'command (append '("pline") coords '("c")))
(setq currobj (ssadd (entlast) currobj))
(command "_layer" "set" "nitride" "")
(command "_layer" "set" "text" "")
(command "_circle" "4799.0625,806.257" "0.075")
(command "_circle" "4799.0625,806.557" "0.075")
(command "_circle" "4799.0625,806.857" "0.075")
(command "_circle" "4799.0625,807.157" "0.075")
(command "_circle" "4799.0625,807.457" "0.075")
(command "_circle" "4798.7625,806.257" "0.075")
(command "_circle" "4798.7625,806.557" "0.075")
(command "_circle" "4798.7625,806.857" "0.075")
(command "_circle" "4798.7625,807.157" "0.075")
(command "_circle" "4798.7625,807.457" "0.075")
(command "_circle" "4798.4625,806.257" "0.075")
(command "_circle" "4798.4625,806.557" "0.075")
(command "_circle" "4798.4625,806.857" "0.075")
(command "_circle" "4798.4625,807.157" "0.075")
(command "_circle" "4798.4625,807.457" "0.075")
(command "_circle" "4798.1625,806.257" "0.075")
(command "_circle" "4798.1625,806.557" "0.075")
(command "_circle" "4798.1625,806.857" "0.075")
(command "_circle" "4798.1625,807.157" "0.075")
(command "_circle" "4798.1625,807.457" "0.075")
(command "_circle" "4797.8625,806.257" "0.075")
(command "_circle" "4797.8625,806.557" "0.075")
(command "_circle" "4797.8625,806.857" "0.075")
(command "_circle" "4797.8625,807.157" "0.075")
(command "_circle" "4797.8625,807.457" "0.075")
(command "_layer" "set" "nitride" "")
(setq coords (list 
(list 4800.2625 831.7) 
(list 4800.2625 836.7) 
(list 4799.7375 836.7) 
(list 4799.7375 831.7)))
(apply 'command (append '("pline") coords '("c")))
(setq currobj (ssadd (entlast) currobj))
(command "_layer" "set" "prebias" "")
(command "_rectangle" "4799.7375,831.7" "4800.2625,836.7")
(setq currobj (ssadd (entlast) currobj))
(command "_layer" "set" "nitride" "")
(setq cooledsinglenanobeam15 currobj)
(setq currobj nil)
(setq currobj (ssadd))
; DRAWING PHOTONIC CRYSTAL
(command "_layer" "set" "negYjunc" "")
(setq coords (list 
(list 4800.125 866.7) 
(list 4800 851.7) 
(list 4800 866.7)))
(apply 'command (append '("pline") coords '("c")))
(setq currobj (ssadd (entlast) currobj))
(setq coords (list 
(list 4800.2625 836.7) 
(list 4800.405 866.7) 
(list 4801.132 866.7) 
(list 4801.132 836.7)))
(apply 'command (append '("pline") coords '("c")))
(setq currobj (ssadd (entlast) currobj))
(setq coords (list 
(list 4799.875 866.7) 
(list 4800 851.7) 
(list 4800 866.7)))
(apply 'command (append '("pline") coords '("c")))
(setq currobj (ssadd (entlast) currobj))
(setq coords (list 
(list 4799.7375 836.7) 
(list 4799.595 866.7) 
(list 4798.868 866.7) 
(list 4798.868 836.7)))
(apply 'command (append '("pline") coords '("c")))
(setq currobj (ssadd (entlast) currobj))
(command "_layer" "set" "nitride" "")
(setq yjunction15 currobj)
(setq currobj nil)
(setq currobj (ssadd))
(setq tap15 nil)
(setq tap15 (ssadd))
(command "_layer" "set" "phc" "")
(setq coords (list 
(list 4800 866.7) 
(list 4800.125 866.7) 
(list 4800.125 866.7103) 
(list 4800.125 866.7206) 
(list 4800.125 866.7308) 
(list 4800.125 866.7411) 
(list 4800.125 866.7514) 
(list 4800.125 866.7617) 
(list 4800.125 866.7719) 
(list 4800.125 866.7822) 
(list 4800.125 866.7925) 
(list 4800.125 866.8028) 
(list 4800.125 866.8131) 
(list 4800.125 866.8233) 
(list 4800.125 866.8336) 
(list 4800.125 866.8439) 
(list 4800.125 866.8542) 
(list 4800.125 866.8644) 
(list 4800.125 866.8747) 
(list 4800.125 866.885) 
(list 4800.125 866.8953) 
(list 4800.125 866.9056) 
(list 4800.125 866.9158) 
(list 4800.125 866.9261) 
(list 4800.125 866.9364) 
(list 4800.125 866.9467) 
(list 4800.125 866.9569) 
(list 4800.125 866.9672) 
(list 4800.125 866.9775) 
(list 4800.125 866.9878) 
(list 4800.125 866.9981) 
(list 4800.125 867.0083) 
(list 4800.125 867.0186) 
(list 4800.125 867.0289) 
(list 4800.125 867.0392) 
(list 4800.125 867.0494) 
(list 4800.125 867.0597) 
(list 4800.125 867.07) 
(list 4800 867.07)))
(apply 'command (append '("pline") coords '("c")))
(setq tap15 (ssadd (entlast) tap15))
(command "_mirror" (entlast) "" "4800,900" "4800,901" "No")
(setq tap15 (ssadd (entlast) tap15))
(setq coords (list 
(list 4800.4157 866.7) 
(list 4800.405 866.7) 
(list 4800.4053 866.7103) 
(list 4800.4056 866.7206) 
(list 4800.4058 866.7308) 
(list 4800.406 866.7411) 
(list 4800.406 866.7514) 
(list 4800.406 866.7617) 
(list 4800.4059 866.7719) 
(list 4800.4057 866.7822) 
(list 4800.4054 866.7925) 
(list 4800.405 866.8028) 
(list 4800.4045 866.8131) 
(list 4800.404 866.8233) 
(list 4800.4035 866.8336) 
(list 4800.4029 866.8439) 
(list 4800.4024 866.8542) 
(list 4800.4019 866.8644) 
(list 4800.4015 866.8747) 
(list 4800.4012 866.885) 
(list 4800.4011 866.8953) 
(list 4800.4011 866.9056) 
(list 4800.4013 866.9158) 
(list 4800.4017 866.9261) 
(list 4800.4023 866.9364) 
(list 4800.403 866.9467) 
(list 4800.4039 866.9569) 
(list 4800.405 866.9672) 
(list 4800.4062 866.9775) 
(list 4800.4075 866.9878) 
(list 4800.4088 866.9981) 
(list 4800.4101 867.0083) 
(list 4800.4114 867.0186) 
(list 4800.4126 867.0289) 
(list 4800.4137 867.0392) 
(list 4800.4146 867.0494) 
(list 4800.4153 867.0597) 
(list 4800.4157 867.07) 
(list 4800.4157 867.07)))
(apply 'command (append '("pline") coords '("c")))
(setq tap15 (ssadd (entlast) tap15))
(command "_mirror" (entlast) "" "4800,900" "4800,901" "No")
(setq tap15 (ssadd (entlast) tap15))
(setq coords (list 
(list 4801.132 866.7) 
(list 4800.4157 866.7) 
(list 4800.4157 866.7103) 
(list 4800.4157 866.7206) 
(list 4800.4157 866.7308) 
(list 4800.4157 866.7411) 
(list 4800.4157 866.7514) 
(list 4800.4157 866.7617) 
(list 4800.4157 866.7719) 
(list 4800.4157 866.7822) 
(list 4800.4157 866.7925) 
(list 4800.4157 866.8028) 
(list 4800.4157 866.8131) 
(list 4800.4157 866.8233) 
(list 4800.4157 866.8336) 
(list 4800.4157 866.8439) 
(list 4800.4157 866.8542) 
(list 4800.4157 866.8644) 
(list 4800.4157 866.8747) 
(list 4800.4157 866.885) 
(list 4800.4157 866.8953) 
(list 4800.4157 866.9056) 
(list 4800.4157 866.9158) 
(list 4800.4157 866.9261) 
(list 4800.4157 866.9364) 
(list 4800.4157 866.9467) 
(list 4800.4157 866.9569) 
(list 4800.4157 866.9672) 
(list 4800.4157 866.9775) 
(list 4800.4157 866.9878) 
(list 4800.4157 866.9981) 
(list 4800.4157 867.0083) 
(list 4800.4157 867.0186) 
(list 4800.4157 867.0289) 
(list 4800.4157 867.0392) 
(list 4800.4157 867.0494) 
(list 4800.4157 867.0597) 
(list 4800.4157 867.07) 
(list 4801.132 867.07)))
(apply 'command (append '("pline") coords '("c")))
(setq tap15 (ssadd (entlast) tap15))
(command "_mirror" (entlast) "" "4800,900" "4800,901" "No")
(setq tap15 (ssadd (entlast) tap15))
(setq coords (list 
(list 4800 867.07) 
(list 4800.125 867.07) 
(list 4800.125 867.0803) 
(list 4800.125 867.0906) 
(list 4800.125 867.1008) 
(list 4800.125 867.1111) 
(list 4800.125 867.1214) 
(list 4800.125 867.1317) 
(list 4800.125 867.1419) 
(list 4800.125 867.1522) 
(list 4800.125 867.1625) 
(list 4800.125 867.1728) 
(list 4800.125 867.1831) 
(list 4800.125 867.1933) 
(list 4800.125 867.2036) 
(list 4800.125 867.2139) 
(list 4800.125 867.2242) 
(list 4800.125 867.2344) 
(list 4800.125 867.2447) 
(list 4800.125 867.255) 
(list 4800.125 867.2653) 
(list 4800.125 867.2756) 
(list 4800.125 867.2858) 
(list 4800.125 867.2961) 
(list 4800.125 867.3064) 
(list 4800.125 867.3167) 
(list 4800.125 867.3269) 
(list 4800.125 867.3372) 
(list 4800.125 867.3475) 
(list 4800.125 867.3578) 
(list 4800.125 867.3681) 
(list 4800.125 867.3783) 
(list 4800.125 867.3886) 
(list 4800.125 867.3989) 
(list 4800.125 867.4092) 
(list 4800.125 867.4194) 
(list 4800.125 867.4297) 
(list 4800.125 867.44) 
(list 4800 867.44)))
(apply 'command (append '("pline") coords '("c")))
(setq tap15 (ssadd (entlast) tap15))
(command "_mirror" (entlast) "" "4800,900" "4800,901" "No")
(setq tap15 (ssadd (entlast) tap15))
(setq coords (list 
(list 4800.4265 867.07) 
(list 4800.4157 867.07) 
(list 4800.4159 867.0803) 
(list 4800.4157 867.0906) 
(list 4800.4153 867.1008) 
(list 4800.4146 867.1111) 
(list 4800.4135 867.1214) 
(list 4800.4122 867.1317) 
(list 4800.4106 867.1419) 
(list 4800.4089 867.1522) 
(list 4800.407 867.1625) 
(list 4800.405 867.1728) 
(list 4800.403 867.1831) 
(list 4800.401 867.1933) 
(list 4800.3992 867.2036) 
(list 4800.3975 867.2139) 
(list 4800.3961 867.2242) 
(list 4800.3949 867.2344) 
(list 4800.3941 867.2447) 
(list 4800.3937 867.255) 
(list 4800.3937 867.2653) 
(list 4800.3941 867.2756) 
(list 4800.395 867.2858) 
(list 4800.3963 867.2961) 
(list 4800.398 867.3064) 
(list 4800.4001 867.3167) 
(list 4800.4024 867.3269) 
(list 4800.405 867.3372) 
(list 4800.4078 867.3475) 
(list 4800.4107 867.3578) 
(list 4800.4135 867.3681) 
(list 4800.4163 867.3783) 
(list 4800.4189 867.3886) 
(list 4800.4212 867.3989) 
(list 4800.4232 867.4092) 
(list 4800.4248 867.4194) 
(list 4800.4259 867.4297) 
(list 4800.4265 867.44) 
(list 4800.4265 867.44)))
(apply 'command (append '("pline") coords '("c")))
(setq tap15 (ssadd (entlast) tap15))
(command "_mirror" (entlast) "" "4800,900" "4800,901" "No")
(setq tap15 (ssadd (entlast) tap15))
(setq coords (list 
(list 4801.132 867.07) 
(list 4800.4265 867.07) 
(list 4800.4265 867.0803) 
(list 4800.4265 867.0906) 
(list 4800.4265 867.1008) 
(list 4800.4265 867.1111) 
(list 4800.4265 867.1214) 
(list 4800.4265 867.1317) 
(list 4800.4265 867.1419) 
(list 4800.4265 867.1522) 
(list 4800.4265 867.1625) 
(list 4800.4265 867.1728) 
(list 4800.4265 867.1831) 
(list 4800.4265 867.1933) 
(list 4800.4265 867.2036) 
(list 4800.4265 867.2139) 
(list 4800.4265 867.2242) 
(list 4800.4265 867.2344) 
(list 4800.4265 867.2447) 
(list 4800.4265 867.255) 
(list 4800.4265 867.2653) 
(list 4800.4265 867.2756) 
(list 4800.4265 867.2858) 
(list 4800.4265 867.2961) 
(list 4800.4265 867.3064) 
(list 4800.4265 867.3167) 
(list 4800.4265 867.3269) 
(list 4800.4265 867.3372) 
(list 4800.4265 867.3475) 
(list 4800.4265 867.3578) 
(list 4800.4265 867.3681) 
(list 4800.4265 867.3783) 
(list 4800.4265 867.3886) 
(list 4800.4265 867.3989) 
(list 4800.4265 867.4092) 
(list 4800.4265 867.4194) 
(list 4800.4265 867.4297) 
(list 4800.4265 867.44) 
(list 4801.132 867.44)))
(apply 'command (append '("pline") coords '("c")))
(setq tap15 (ssadd (entlast) tap15))
(command "_mirror" (entlast) "" "4800,900" "4800,901" "No")
(setq tap15 (ssadd (entlast) tap15))
(setq coords (list 
(list 4800 867.44) 
(list 4800.125 867.44) 
(list 4800.125 867.4503) 
(list 4800.125 867.4606) 
(list 4800.125 867.4708) 
(list 4800.125 867.4811) 
(list 4800.125 867.4914) 
(list 4800.125 867.5017) 
(list 4800.125 867.5119) 
(list 4800.125 867.5222) 
(list 4800.125 867.5325) 
(list 4800.125 867.5428) 
(list 4800.125 867.5531) 
(list 4800.125 867.5633) 
(list 4800.125 867.5736) 
(list 4800.125 867.5839) 
(list 4800.125 867.5942) 
(list 4800.125 867.6044) 
(list 4800.125 867.6147) 
(list 4800.125 867.625) 
(list 4800.125 867.6353) 
(list 4800.125 867.6456) 
(list 4800.125 867.6558) 
(list 4800.125 867.6661) 
(list 4800.125 867.6764) 
(list 4800.125 867.6867) 
(list 4800.125 867.6969) 
(list 4800.125 867.7072) 
(list 4800.125 867.7175) 
(list 4800.125 867.7278) 
(list 4800.125 867.7381) 
(list 4800.125 867.7483) 
(list 4800.125 867.7586) 
(list 4800.125 867.7689) 
(list 4800.125 867.7792) 
(list 4800.125 867.7894) 
(list 4800.125 867.7997) 
(list 4800.125 867.81) 
(list 4800 867.81)))
(apply 'command (append '("pline") coords '("c")))
(setq tap15 (ssadd (entlast) tap15))
(command "_mirror" (entlast) "" "4800,900" "4800,901" "No")
(setq tap15 (ssadd (entlast) tap15))
(setq coords (list 
(list 4800.4372 867.44) 
(list 4800.4265 867.44) 
(list 4800.4265 867.4503) 
(list 4800.4259 867.4606) 
(list 4800.4248 867.4708) 
(list 4800.4231 867.4811) 
(list 4800.421 867.4914) 
(list 4800.4184 867.5017) 
(list 4800.4154 867.5119) 
(list 4800.4121 867.5222) 
(list 4800.4086 867.5325) 
(list 4800.405 867.5428) 
(list 4800.4015 867.5531) 
(list 4800.3981 867.5633) 
(list 4800.3949 867.5736) 
(list 4800.3921 867.5839) 
(list 4800.3898 867.5942) 
(list 4800.3879 867.6044) 
(list 4800.3867 867.6147) 
(list 4800.3862 867.625) 
(list 4800.3863 867.6353) 
(list 4800.3872 867.6456) 
(list 4800.3887 867.6558) 
(list 4800.3909 867.6661) 
(list 4800.3937 867.6764) 
(list 4800.3971 867.6867) 
(list 4800.4009 867.6969) 
(list 4800.405 867.7072) 
(list 4800.4094 867.7175) 
(list 4800.4138 867.7278) 
(list 4800.4183 867.7381) 
(list 4800.4225 867.7483) 
(list 4800.4264 867.7586) 
(list 4800.4298 867.7689) 
(list 4800.4327 867.7792) 
(list 4800.435 867.7894) 
(list 4800.4365 867.7997) 
(list 4800.4372 867.81) 
(list 4800.4372 867.81)))
(apply 'command (append '("pline") coords '("c")))
(setq tap15 (ssadd (entlast) tap15))
(command "_mirror" (entlast) "" "4800,900" "4800,901" "No")
(setq tap15 (ssadd (entlast) tap15))
(setq coords (list 
(list 4801.132 867.44) 
(list 4800.4372 867.44) 
(list 4800.4372 867.4503) 
(list 4800.4372 867.4606) 
(list 4800.4372 867.4708) 
(list 4800.4372 867.4811) 
(list 4800.4372 867.4914) 
(list 4800.4372 867.5017) 
(list 4800.4372 867.5119) 
(list 4800.4372 867.5222) 
(list 4800.4372 867.5325) 
(list 4800.4372 867.5428) 
(list 4800.4372 867.5531) 
(list 4800.4372 867.5633) 
(list 4800.4372 867.5736) 
(list 4800.4372 867.5839) 
(list 4800.4372 867.5942) 
(list 4800.4372 867.6044) 
(list 4800.4372 867.6147) 
(list 4800.4372 867.625) 
(list 4800.4372 867.6353) 
(list 4800.4372 867.6456) 
(list 4800.4372 867.6558) 
(list 4800.4372 867.6661) 
(list 4800.4372 867.6764) 
(list 4800.4372 867.6867) 
(list 4800.4372 867.6969) 
(list 4800.4372 867.7072) 
(list 4800.4372 867.7175) 
(list 4800.4372 867.7278) 
(list 4800.4372 867.7381) 
(list 4800.4372 867.7483) 
(list 4800.4372 867.7586) 
(list 4800.4372 867.7689) 
(list 4800.4372 867.7792) 
(list 4800.4372 867.7894) 
(list 4800.4372 867.7997) 
(list 4800.4372 867.81) 
(list 4801.132 867.81)))
(apply 'command (append '("pline") coords '("c")))
(setq tap15 (ssadd (entlast) tap15))
(command "_mirror" (entlast) "" "4800,900" "4800,901" "No")
(setq tap15 (ssadd (entlast) tap15))
(setq coords (list 
(list 4800 867.81) 
(list 4800.125 867.81) 
(list 4800.125 867.8203) 
(list 4800.125 867.8306) 
(list 4800.125 867.8408) 
(list 4800.125 867.8511) 
(list 4800.125 867.8614) 
(list 4800.125 867.8717) 
(list 4800.125 867.8819) 
(list 4800.125 867.8922) 
(list 4800.125 867.9025) 
(list 4800.125 867.9128) 
(list 4800.125 867.9231) 
(list 4800.125 867.9333) 
(list 4800.125 867.9436) 
(list 4800.125 867.9539) 
(list 4800.125 867.9642) 
(list 4800.125 867.9744) 
(list 4800.125 867.9847) 
(list 4800.125 867.995) 
(list 4800.125 868.0053) 
(list 4800.125 868.0156) 
(list 4800.125 868.0258) 
(list 4800.125 868.0361) 
(list 4800.125 868.0464) 
(list 4800.125 868.0567) 
(list 4800.125 868.0669) 
(list 4800.125 868.0772) 
(list 4800.125 868.0875) 
(list 4800.125 868.0978) 
(list 4800.125 868.1081) 
(list 4800.125 868.1183) 
(list 4800.125 868.1286) 
(list 4800.125 868.1389) 
(list 4800.125 868.1492) 
(list 4800.125 868.1594) 
(list 4800.125 868.1697) 
(list 4800.125 868.18) 
(list 4800 868.18)))
(apply 'command (append '("pline") coords '("c")))
(setq tap15 (ssadd (entlast) tap15))
(command "_mirror" (entlast) "" "4800,900" "4800,901" "No")
(setq tap15 (ssadd (entlast) tap15))
(setq coords (list 
(list 4800.4479 867.81) 
(list 4800.4372 867.81) 
(list 4800.4371 867.8203) 
(list 4800.4361 867.8306) 
(list 4800.4343 867.8408) 
(list 4800.4317 867.8511) 
(list 4800.4285 867.8614) 
(list 4800.4245 867.8717) 
(list 4800.4201 867.8819) 
(list 4800.4153 867.8922) 
(list 4800.4102 867.9025) 
(list 4800.405 867.9128) 
(list 4800.4 867.9231) 
(list 4800.3951 867.9333) 
(list 4800.3906 867.9436) 
(list 4800.3867 867.9539) 
(list 4800.3834 867.9642) 
(list 4800.3809 867.9744) 
(list 4800.3793 867.9847) 
(list 4800.3786 867.995) 
(list 4800.3789 868.0053) 
(list 4800.3802 868.0156) 
(list 4800.3824 868.0258) 
(list 4800.3855 868.0361) 
(list 4800.3895 868.0464) 
(list 4800.3941 868.0567) 
(list 4800.3994 868.0669) 
(list 4800.4051 868.0772) 
(list 4800.411 868.0875) 
(list 4800.417 868.0978) 
(list 4800.423 868.1081) 
(list 4800.4286 868.1183) 
(list 4800.4338 868.1286) 
(list 4800.4384 868.1389) 
(list 4800.4422 868.1492) 
(list 4800.4452 868.1594) 
(list 4800.4471 868.1697) 
(list 4800.4479 868.18) 
(list 4800.4479 868.18)))
(apply 'command (append '("pline") coords '("c")))
(setq tap15 (ssadd (entlast) tap15))
(command "_mirror" (entlast) "" "4800,900" "4800,901" "No")
(setq tap15 (ssadd (entlast) tap15))
(setq coords (list 
(list 4801.132 867.81) 
(list 4800.4479 867.81) 
(list 4800.4479 867.8203) 
(list 4800.4479 867.8306) 
(list 4800.4479 867.8408) 
(list 4800.4479 867.8511) 
(list 4800.4479 867.8614) 
(list 4800.4479 867.8717) 
(list 4800.4479 867.8819) 
(list 4800.4479 867.8922) 
(list 4800.4479 867.9025) 
(list 4800.4479 867.9128) 
(list 4800.4479 867.9231) 
(list 4800.4479 867.9333) 
(list 4800.4479 867.9436) 
(list 4800.4479 867.9539) 
(list 4800.4479 867.9642) 
(list 4800.4479 867.9744) 
(list 4800.4479 867.9847) 
(list 4800.4479 867.995) 
(list 4800.4479 868.0053) 
(list 4800.4479 868.0156) 
(list 4800.4479 868.0258) 
(list 4800.4479 868.0361) 
(list 4800.4479 868.0464) 
(list 4800.4479 868.0567) 
(list 4800.4479 868.0669) 
(list 4800.4479 868.0772) 
(list 4800.4479 868.0875) 
(list 4800.4479 868.0978) 
(list 4800.4479 868.1081) 
(list 4800.4479 868.1183) 
(list 4800.4479 868.1286) 
(list 4800.4479 868.1389) 
(list 4800.4479 868.1492) 
(list 4800.4479 868.1594) 
(list 4800.4479 868.1697) 
(list 4800.4479 868.18) 
(list 4801.132 868.18)))
(apply 'command (append '("pline") coords '("c")))
(setq tap15 (ssadd (entlast) tap15))
(command "_mirror" (entlast) "" "4800,900" "4800,901" "No")
(setq tap15 (ssadd (entlast) tap15))
(setq coords (list 
(list 4800 868.18) 
(list 4800.125 868.18) 
(list 4800.125 868.1903) 
(list 4800.125 868.2006) 
(list 4800.125 868.2108) 
(list 4800.125 868.2211) 
(list 4800.125 868.2314) 
(list 4800.125 868.2417) 
(list 4800.125 868.2519) 
(list 4800.125 868.2622) 
(list 4800.125 868.2725) 
(list 4800.125 868.2828) 
(list 4800.125 868.2931) 
(list 4800.125 868.3033) 
(list 4800.125 868.3136) 
(list 4800.125 868.3239) 
(list 4800.125 868.3342) 
(list 4800.125 868.3444) 
(list 4800.125 868.3547) 
(list 4800.125 868.365) 
(list 4800.125 868.3753) 
(list 4800.125 868.3856) 
(list 4800.125 868.3958) 
(list 4800.125 868.4061) 
(list 4800.125 868.4164) 
(list 4800.125 868.4267) 
(list 4800.125 868.4369) 
(list 4800.125 868.4472) 
(list 4800.125 868.4575) 
(list 4800.125 868.4678) 
(list 4800.125 868.4781) 
(list 4800.125 868.4883) 
(list 4800.125 868.4986) 
(list 4800.125 868.5089) 
(list 4800.125 868.5192) 
(list 4800.125 868.5294) 
(list 4800.125 868.5397) 
(list 4800.125 868.55) 
(list 4800 868.55)))
(apply 'command (append '("pline") coords '("c")))
(setq tap15 (ssadd (entlast) tap15))
(command "_mirror" (entlast) "" "4800,900" "4800,901" "No")
(setq tap15 (ssadd (entlast) tap15))
(setq coords (list 
(list 4800.4587 868.18) 
(list 4800.4479 868.18) 
(list 4800.4477 868.1903) 
(list 4800.4463 868.2006) 
(list 4800.4438 868.2108) 
(list 4800.4403 868.2211) 
(list 4800.4359 868.2314) 
(list 4800.4307 868.2417) 
(list 4800.4248 868.2519) 
(list 4800.4185 868.2622) 
(list 4800.4118 868.2725) 
(list 4800.4051 868.2828) 
(list 4800.3984 868.2931) 
(list 4800.3921 868.3033) 
(list 4800.3864 868.3136) 
(list 4800.3813 868.3239) 
(list 4800.3771 868.3342) 
(list 4800.374 868.3444) 
(list 4800.3719 868.3547) 
(list 4800.3711 868.365) 
(list 4800.3715 868.3753) 
(list 4800.3732 868.3856) 
(list 4800.3761 868.3958) 
(list 4800.3801 868.4061) 
(list 4800.3852 868.4164) 
(list 4800.3912 868.4267) 
(list 4800.3978 868.4369) 
(list 4800.4051 868.4472) 
(list 4800.4126 868.4575) 
(list 4800.4202 868.4678) 
(list 4800.4277 868.4781) 
(list 4800.4348 868.4883) 
(list 4800.4413 868.4986) 
(list 4800.447 868.5089) 
(list 4800.4518 868.5192) 
(list 4800.4553 868.5294) 
(list 4800.4577 868.5397) 
(list 4800.4587 868.55) 
(list 4800.4587 868.55)))
(apply 'command (append '("pline") coords '("c")))
(setq tap15 (ssadd (entlast) tap15))
(command "_mirror" (entlast) "" "4800,900" "4800,901" "No")
(setq tap15 (ssadd (entlast) tap15))
(setq coords (list 
(list 4801.132 868.18) 
(list 4800.4587 868.18) 
(list 4800.4587 868.1903) 
(list 4800.4587 868.2006) 
(list 4800.4587 868.2108) 
(list 4800.4587 868.2211) 
(list 4800.4587 868.2314) 
(list 4800.4587 868.2417) 
(list 4800.4587 868.2519) 
(list 4800.4587 868.2622) 
(list 4800.4587 868.2725) 
(list 4800.4587 868.2828) 
(list 4800.4587 868.2931) 
(list 4800.4587 868.3033) 
(list 4800.4587 868.3136) 
(list 4800.4587 868.3239) 
(list 4800.4587 868.3342) 
(list 4800.4587 868.3444) 
(list 4800.4587 868.3547) 
(list 4800.4587 868.365) 
(list 4800.4587 868.3753) 
(list 4800.4587 868.3856) 
(list 4800.4587 868.3958) 
(list 4800.4587 868.4061) 
(list 4800.4587 868.4164) 
(list 4800.4587 868.4267) 
(list 4800.4587 868.4369) 
(list 4800.4587 868.4472) 
(list 4800.4587 868.4575) 
(list 4800.4587 868.4678) 
(list 4800.4587 868.4781) 
(list 4800.4587 868.4883) 
(list 4800.4587 868.4986) 
(list 4800.4587 868.5089) 
(list 4800.4587 868.5192) 
(list 4800.4587 868.5294) 
(list 4800.4587 868.5397) 
(list 4800.4587 868.55) 
(list 4801.132 868.55)))
(apply 'command (append '("pline") coords '("c")))
(setq tap15 (ssadd (entlast) tap15))
(command "_mirror" (entlast) "" "4800,900" "4800,901" "No")
(setq tap15 (ssadd (entlast) tap15))
(setq coords (list 
(list 4800 868.55) 
(list 4800.125 868.55) 
(list 4800.125 868.5603) 
(list 4800.125 868.5706) 
(list 4800.125 868.5808) 
(list 4800.125 868.5911) 
(list 4800.125 868.6014) 
(list 4800.125 868.6117) 
(list 4800.125 868.6219) 
(list 4800.125 868.6322) 
(list 4800.125 868.6425) 
(list 4800.125 868.6528) 
(list 4800.125 868.6631) 
(list 4800.125 868.6733) 
(list 4800.125 868.6836) 
(list 4800.125 868.6939) 
(list 4800.125 868.7042) 
(list 4800.125 868.7144) 
(list 4800.125 868.7247) 
(list 4800.125 868.735) 
(list 4800.125 868.7453) 
(list 4800.125 868.7556) 
(list 4800.125 868.7658) 
(list 4800.125 868.7761) 
(list 4800.125 868.7864) 
(list 4800.125 868.7967) 
(list 4800.125 868.8069) 
(list 4800.125 868.8172) 
(list 4800.125 868.8275) 
(list 4800.125 868.8378) 
(list 4800.125 868.8481) 
(list 4800.125 868.8583) 
(list 4800.125 868.8686) 
(list 4800.125 868.8789) 
(list 4800.125 868.8892) 
(list 4800.125 868.8994) 
(list 4800.125 868.9097) 
(list 4800.125 868.92) 
(list 4800 868.92)))
(apply 'command (append '("pline") coords '("c")))
(setq tap15 (ssadd (entlast) tap15))
(command "_mirror" (entlast) "" "4800,900" "4800,901" "No")
(setq tap15 (ssadd (entlast) tap15))
(setq coords (list 
(list 4800.4694 868.55) 
(list 4800.4587 868.55) 
(list 4800.4583 868.5603) 
(list 4800.4565 868.5706) 
(list 4800.4533 868.5808) 
(list 4800.4489 868.5911) 
(list 4800.4434 868.6014) 
(list 4800.4369 868.6117) 
(list 4800.4295 868.6219) 
(list 4800.4216 868.6322) 
(list 4800.4134 868.6425) 
(list 4800.4051 868.6528) 
(list 4800.3969 868.6631) 
(list 4800.3892 868.6733) 
(list 4800.3821 868.6836) 
(list 4800.3759 868.6939) 
(list 4800.3708 868.7042) 
(list 4800.367 868.7144) 
(list 4800.3645 868.7247) 
(list 4800.3636 868.735) 
(list 4800.3641 868.7453) 
(list 4800.3662 868.7556) 
(list 4800.3698 868.7658) 
(list 4800.3747 868.7761) 
(list 4800.3809 868.7864) 
(list 4800.3882 868.7967) 
(list 4800.3963 868.8069) 
(list 4800.4051 868.8172) 
(list 4800.4142 868.8275) 
(list 4800.4234 868.8378) 
(list 4800.4324 868.8481) 
(list 4800.441 868.8583) 
(list 4800.4488 868.8686) 
(list 4800.4556 868.8789) 
(list 4800.4613 868.8892) 
(list 4800.4655 868.8994) 
(list 4800.4683 868.9097) 
(list 4800.4694 868.92) 
(list 4800.4694 868.92)))
(apply 'command (append '("pline") coords '("c")))
(setq tap15 (ssadd (entlast) tap15))
(command "_mirror" (entlast) "" "4800,900" "4800,901" "No")
(setq tap15 (ssadd (entlast) tap15))
(setq coords (list 
(list 4801.132 868.55) 
(list 4800.4694 868.55) 
(list 4800.4694 868.5603) 
(list 4800.4694 868.5706) 
(list 4800.4694 868.5808) 
(list 4800.4694 868.5911) 
(list 4800.4694 868.6014) 
(list 4800.4694 868.6117) 
(list 4800.4694 868.6219) 
(list 4800.4694 868.6322) 
(list 4800.4694 868.6425) 
(list 4800.4694 868.6528) 
(list 4800.4694 868.6631) 
(list 4800.4694 868.6733) 
(list 4800.4694 868.6836) 
(list 4800.4694 868.6939) 
(list 4800.4694 868.7042) 
(list 4800.4694 868.7144) 
(list 4800.4694 868.7247) 
(list 4800.4694 868.735) 
(list 4800.4694 868.7453) 
(list 4800.4694 868.7556) 
(list 4800.4694 868.7658) 
(list 4800.4694 868.7761) 
(list 4800.4694 868.7864) 
(list 4800.4694 868.7967) 
(list 4800.4694 868.8069) 
(list 4800.4694 868.8172) 
(list 4800.4694 868.8275) 
(list 4800.4694 868.8378) 
(list 4800.4694 868.8481) 
(list 4800.4694 868.8583) 
(list 4800.4694 868.8686) 
(list 4800.4694 868.8789) 
(list 4800.4694 868.8892) 
(list 4800.4694 868.8994) 
(list 4800.4694 868.9097) 
(list 4800.4694 868.92) 
(list 4801.132 868.92)))
(apply 'command (append '("pline") coords '("c")))
(setq tap15 (ssadd (entlast) tap15))
(command "_mirror" (entlast) "" "4800,900" "4800,901" "No")
(setq tap15 (ssadd (entlast) tap15))
(setq coords (list 
(list 4800 868.92) 
(list 4800.125 868.92) 
(list 4800.125 868.9303) 
(list 4800.125 868.9406) 
(list 4800.125 868.9508) 
(list 4800.125 868.9611) 
(list 4800.125 868.9714) 
(list 4800.125 868.9817) 
(list 4800.125 868.9919) 
(list 4800.125 869.0022) 
(list 4800.125 869.0125) 
(list 4800.125 869.0228) 
(list 4800.125 869.0331) 
(list 4800.125 869.0433) 
(list 4800.125 869.0536) 
(list 4800.125 869.0639) 
(list 4800.125 869.0742) 
(list 4800.125 869.0844) 
(list 4800.125 869.0947) 
(list 4800.125 869.105) 
(list 4800.125 869.1153) 
(list 4800.125 869.1256) 
(list 4800.125 869.1358) 
(list 4800.125 869.1461) 
(list 4800.125 869.1564) 
(list 4800.125 869.1667) 
(list 4800.125 869.1769) 
(list 4800.125 869.1872) 
(list 4800.125 869.1975) 
(list 4800.125 869.2078) 
(list 4800.125 869.2181) 
(list 4800.125 869.2283) 
(list 4800.125 869.2386) 
(list 4800.125 869.2489) 
(list 4800.125 869.2592) 
(list 4800.125 869.2694) 
(list 4800.125 869.2797) 
(list 4800.125 869.29) 
(list 4800 869.29)))
(apply 'command (append '("pline") coords '("c")))
(setq tap15 (ssadd (entlast) tap15))
(command "_mirror" (entlast) "" "4800,900" "4800,901" "No")
(setq tap15 (ssadd (entlast) tap15))
(setq coords (list 
(list 4800.4801 868.92) 
(list 4800.4694 868.92) 
(list 4800.4689 868.9303) 
(list 4800.4667 868.9406) 
(list 4800.4628 868.9508) 
(list 4800.4575 868.9611) 
(list 4800.4509 868.9714) 
(list 4800.443 868.9817) 
(list 4800.4343 868.9919) 
(list 4800.4248 869.0022) 
(list 4800.415 869.0125) 
(list 4800.4051 869.0228) 
(list 4800.3954 869.0331) 
(list 4800.3862 869.0433) 
(list 4800.3778 869.0536) 
(list 4800.3705 869.0639) 
(list 4800.3645 869.0742) 
(list 4800.36 869.0844) 
(list 4800.3571 869.0947) 
(list 4800.356 869.105) 
(list 4800.3567 869.1153) 
(list 4800.3592 869.1256) 
(list 4800.3635 869.1358) 
(list 4800.3693 869.1461) 
(list 4800.3766 869.1564) 
(list 4800.3852 869.1667) 
(list 4800.3948 869.1769) 
(list 4800.4051 869.1872) 
(list 4800.4158 869.1975) 
(list 4800.4266 869.2078) 
(list 4800.4371 869.2181) 
(list 4800.4471 869.2283) 
(list 4800.4563 869.2386) 
(list 4800.4642 869.2489) 
(list 4800.4708 869.2592) 
(list 4800.4757 869.2694) 
(list 4800.4789 869.2797) 
(list 4800.4801 869.29) 
(list 4800.4801 869.29)))
(apply 'command (append '("pline") coords '("c")))
(setq tap15 (ssadd (entlast) tap15))
(command "_mirror" (entlast) "" "4800,900" "4800,901" "No")
(setq tap15 (ssadd (entlast) tap15))
(setq coords (list 
(list 4801.132 868.92) 
(list 4800.4801 868.92) 
(list 4800.4801 868.9303) 
(list 4800.4801 868.9406) 
(list 4800.4801 868.9508) 
(list 4800.4801 868.9611) 
(list 4800.4801 868.9714) 
(list 4800.4801 868.9817) 
(list 4800.4801 868.9919) 
(list 4800.4801 869.0022) 
(list 4800.4801 869.0125) 
(list 4800.4801 869.0228) 
(list 4800.4801 869.0331) 
(list 4800.4801 869.0433) 
(list 4800.4801 869.0536) 
(list 4800.4801 869.0639) 
(list 4800.4801 869.0742) 
(list 4800.4801 869.0844) 
(list 4800.4801 869.0947) 
(list 4800.4801 869.105) 
(list 4800.4801 869.1153) 
(list 4800.4801 869.1256) 
(list 4800.4801 869.1358) 
(list 4800.4801 869.1461) 
(list 4800.4801 869.1564) 
(list 4800.4801 869.1667) 
(list 4800.4801 869.1769) 
(list 4800.4801 869.1872) 
(list 4800.4801 869.1975) 
(list 4800.4801 869.2078) 
(list 4800.4801 869.2181) 
(list 4800.4801 869.2283) 
(list 4800.4801 869.2386) 
(list 4800.4801 869.2489) 
(list 4800.4801 869.2592) 
(list 4800.4801 869.2694) 
(list 4800.4801 869.2797) 
(list 4800.4801 869.29) 
(list 4801.132 869.29)))
(apply 'command (append '("pline") coords '("c")))
(setq tap15 (ssadd (entlast) tap15))
(command "_mirror" (entlast) "" "4800,900" "4800,901" "No")
(setq tap15 (ssadd (entlast) tap15))
(setq coords (list 
(list 4800 869.29) 
(list 4800.125 869.29) 
(list 4800.125 869.3003) 
(list 4800.125 869.3106) 
(list 4800.125 869.3208) 
(list 4800.125 869.3311) 
(list 4800.125 869.3414) 
(list 4800.125 869.3517) 
(list 4800.125 869.3619) 
(list 4800.125 869.3722) 
(list 4800.125 869.3825) 
(list 4800.125 869.3928) 
(list 4800.125 869.4031) 
(list 4800.125 869.4133) 
(list 4800.125 869.4236) 
(list 4800.125 869.4339) 
(list 4800.125 869.4442) 
(list 4800.125 869.4544) 
(list 4800.125 869.4647) 
(list 4800.125 869.475) 
(list 4800.125 869.4853) 
(list 4800.125 869.4956) 
(list 4800.125 869.5058) 
(list 4800.125 869.5161) 
(list 4800.125 869.5264) 
(list 4800.125 869.5367) 
(list 4800.125 869.5469) 
(list 4800.125 869.5572) 
(list 4800.125 869.5675) 
(list 4800.125 869.5778) 
(list 4800.125 869.5881) 
(list 4800.125 869.5983) 
(list 4800.125 869.6086) 
(list 4800.125 869.6189) 
(list 4800.125 869.6292) 
(list 4800.125 869.6394) 
(list 4800.125 869.6497) 
(list 4800.125 869.66) 
(list 4800 869.66)))
(apply 'command (append '("pline") coords '("c")))
(setq tap15 (ssadd (entlast) tap15))
(command "_mirror" (entlast) "" "4800,900" "4800,901" "No")
(setq tap15 (ssadd (entlast) tap15))
(setq coords (list 
(list 4800.4909 869.29) 
(list 4800.4801 869.29) 
(list 4800.4795 869.3003) 
(list 4800.4768 869.3106) 
(list 4800.4724 869.3208) 
(list 4800.4661 869.3311) 
(list 4800.4583 869.3414) 
(list 4800.4492 869.3517) 
(list 4800.439 869.3619) 
(list 4800.428 869.3722) 
(list 4800.4166 869.3825) 
(list 4800.4051 869.3928) 
(list 4800.3939 869.4031) 
(list 4800.3832 869.4133) 
(list 4800.3736 869.4236) 
(list 4800.3651 869.4339) 
(list 4800.3582 869.4442) 
(list 4800.353 869.4544) 
(list 4800.3497 869.4647) 
(list 4800.3485 869.475) 
(list 4800.3493 869.4853) 
(list 4800.3522 869.4956) 
(list 4800.3572 869.5058) 
(list 4800.3639 869.5161) 
(list 4800.3724 869.5264) 
(list 4800.3823 869.5367) 
(list 4800.3933 869.5469) 
(list 4800.4051 869.5572) 
(list 4800.4174 869.5675) 
(list 4800.4298 869.5778) 
(list 4800.4419 869.5881) 
(list 4800.4533 869.5983) 
(list 4800.4637 869.6086) 
(list 4800.4728 869.6189) 
(list 4800.4803 869.6292) 
(list 4800.4859 869.6394) 
(list 4800.4895 869.6497) 
(list 4800.4909 869.66) 
(list 4800.4909 869.66)))
(apply 'command (append '("pline") coords '("c")))
(setq tap15 (ssadd (entlast) tap15))
(command "_mirror" (entlast) "" "4800,900" "4800,901" "No")
(setq tap15 (ssadd (entlast) tap15))
(setq coords (list 
(list 4801.132 869.29) 
(list 4800.4909 869.29) 
(list 4800.4909 869.3003) 
(list 4800.4909 869.3106) 
(list 4800.4909 869.3208) 
(list 4800.4909 869.3311) 
(list 4800.4909 869.3414) 
(list 4800.4909 869.3517) 
(list 4800.4909 869.3619) 
(list 4800.4909 869.3722) 
(list 4800.4909 869.3825) 
(list 4800.4909 869.3928) 
(list 4800.4909 869.4031) 
(list 4800.4909 869.4133) 
(list 4800.4909 869.4236) 
(list 4800.4909 869.4339) 
(list 4800.4909 869.4442) 
(list 4800.4909 869.4544) 
(list 4800.4909 869.4647) 
(list 4800.4909 869.475) 
(list 4800.4909 869.4853) 
(list 4800.4909 869.4956) 
(list 4800.4909 869.5058) 
(list 4800.4909 869.5161) 
(list 4800.4909 869.5264) 
(list 4800.4909 869.5367) 
(list 4800.4909 869.5469) 
(list 4800.4909 869.5572) 
(list 4800.4909 869.5675) 
(list 4800.4909 869.5778) 
(list 4800.4909 869.5881) 
(list 4800.4909 869.5983) 
(list 4800.4909 869.6086) 
(list 4800.4909 869.6189) 
(list 4800.4909 869.6292) 
(list 4800.4909 869.6394) 
(list 4800.4909 869.6497) 
(list 4800.4909 869.66) 
(list 4801.132 869.66)))
(apply 'command (append '("pline") coords '("c")))
(setq tap15 (ssadd (entlast) tap15))
(command "_mirror" (entlast) "" "4800,900" "4800,901" "No")
(setq tap15 (ssadd (entlast) tap15))
(setq coords (list 
(list 4800 869.66) 
(list 4800.125 869.66) 
(list 4800.125 869.6703) 
(list 4800.125 869.6806) 
(list 4800.125 869.6908) 
(list 4800.125 869.7011) 
(list 4800.125 869.7114) 
(list 4800.125 869.7217) 
(list 4800.125 869.7319) 
(list 4800.125 869.7422) 
(list 4800.125 869.7525) 
(list 4800.125 869.7628) 
(list 4800.125 869.7731) 
(list 4800.125 869.7833) 
(list 4800.125 869.7936) 
(list 4800.125 869.8039) 
(list 4800.125 869.8142) 
(list 4800.125 869.8244) 
(list 4800.125 869.8347) 
(list 4800.125 869.845) 
(list 4800.125 869.8553) 
(list 4800.125 869.8656) 
(list 4800.125 869.8758) 
(list 4800.125 869.8861) 
(list 4800.125 869.8964) 
(list 4800.125 869.9067) 
(list 4800.125 869.9169) 
(list 4800.125 869.9272) 
(list 4800.125 869.9375) 
(list 4800.125 869.9478) 
(list 4800.125 869.9581) 
(list 4800.125 869.9683) 
(list 4800.125 869.9786) 
(list 4800.125 869.9889) 
(list 4800.125 869.9992) 
(list 4800.125 870.0094) 
(list 4800.125 870.0197) 
(list 4800.125 870.03) 
(list 4800 870.03)))
(apply 'command (append '("pline") coords '("c")))
(setq tap15 (ssadd (entlast) tap15))
(command "_mirror" (entlast) "" "4800,900" "4800,901" "No")
(setq tap15 (ssadd (entlast) tap15))
(setq coords (list 
(list 4800.5016 869.66) 
(list 4800.4909 869.66) 
(list 4800.4901 869.6703) 
(list 4800.487 869.6806) 
(list 4800.4819 869.6908) 
(list 4800.4747 869.7011) 
(list 4800.4658 869.7114) 
(list 4800.4554 869.7217) 
(list 4800.4437 869.7319) 
(list 4800.4312 869.7422) 
(list 4800.4182 869.7525) 
(list 4800.4051 869.7628) 
(list 4800.3923 869.7731) 
(list 4800.3803 869.7833) 
(list 4800.3693 869.7936) 
(list 4800.3597 869.8039) 
(list 4800.3519 869.8142) 
(list 4800.346 869.8244) 
(list 4800.3424 869.8347) 
(list 4800.341 869.845) 
(list 4800.3419 869.8553) 
(list 4800.3453 869.8656) 
(list 4800.3508 869.8758) 
(list 4800.3585 869.8861) 
(list 4800.3681 869.8964) 
(list 4800.3793 869.9067) 
(list 4800.3918 869.9169) 
(list 4800.4051 869.9272) 
(list 4800.419 869.9375) 
(list 4800.433 869.9478) 
(list 4800.4466 869.9581) 
(list 4800.4595 869.9683) 
(list 4800.4712 869.9786) 
(list 4800.4814 869.9889) 
(list 4800.4898 869.9992) 
(list 4800.4961 870.0094) 
(list 4800.5001 870.0197) 
(list 4800.5016 870.03) 
(list 4800.5016 870.03)))
(apply 'command (append '("pline") coords '("c")))
(setq tap15 (ssadd (entlast) tap15))
(command "_mirror" (entlast) "" "4800,900" "4800,901" "No")
(setq tap15 (ssadd (entlast) tap15))
(setq coords (list 
(list 4801.132 869.66) 
(list 4800.5016 869.66) 
(list 4800.5016 869.6703) 
(list 4800.5016 869.6806) 
(list 4800.5016 869.6908) 
(list 4800.5016 869.7011) 
(list 4800.5016 869.7114) 
(list 4800.5016 869.7217) 
(list 4800.5016 869.7319) 
(list 4800.5016 869.7422) 
(list 4800.5016 869.7525) 
(list 4800.5016 869.7628) 
(list 4800.5016 869.7731) 
(list 4800.5016 869.7833) 
(list 4800.5016 869.7936) 
(list 4800.5016 869.8039) 
(list 4800.5016 869.8142) 
(list 4800.5016 869.8244) 
(list 4800.5016 869.8347) 
(list 4800.5016 869.845) 
(list 4800.5016 869.8553) 
(list 4800.5016 869.8656) 
(list 4800.5016 869.8758) 
(list 4800.5016 869.8861) 
(list 4800.5016 869.8964) 
(list 4800.5016 869.9067) 
(list 4800.5016 869.9169) 
(list 4800.5016 869.9272) 
(list 4800.5016 869.9375) 
(list 4800.5016 869.9478) 
(list 4800.5016 869.9581) 
(list 4800.5016 869.9683) 
(list 4800.5016 869.9786) 
(list 4800.5016 869.9889) 
(list 4800.5016 869.9992) 
(list 4800.5016 870.0094) 
(list 4800.5016 870.0197) 
(list 4800.5016 870.03) 
(list 4801.132 870.03)))
(apply 'command (append '("pline") coords '("c")))
(setq tap15 (ssadd (entlast) tap15))
(command "_mirror" (entlast) "" "4800,900" "4800,901" "No")
(setq tap15 (ssadd (entlast) tap15))
(setq coords (list 
(list 4800 870.03) 
(list 4800.125 870.03) 
(list 4800.125 870.0403) 
(list 4800.125 870.0506) 
(list 4800.125 870.0608) 
(list 4800.125 870.0711) 
(list 4800.125 870.0814) 
(list 4800.125 870.0917) 
(list 4800.125 870.1019) 
(list 4800.125 870.1122) 
(list 4800.125 870.1225) 
(list 4800.125 870.1328) 
(list 4800.125 870.1431) 
(list 4800.125 870.1533) 
(list 4800.125 870.1636) 
(list 4800.125 870.1739) 
(list 4800.125 870.1842) 
(list 4800.125 870.1944) 
(list 4800.125 870.2047) 
(list 4800.125 870.215) 
(list 4800.125 870.2253) 
(list 4800.125 870.2356) 
(list 4800.125 870.2458) 
(list 4800.125 870.2561) 
(list 4800.125 870.2664) 
(list 4800.125 870.2767) 
(list 4800.125 870.2869) 
(list 4800.125 870.2972) 
(list 4800.125 870.3075) 
(list 4800.125 870.3178) 
(list 4800.125 870.3281) 
(list 4800.125 870.3383) 
(list 4800.125 870.3486) 
(list 4800.125 870.3589) 
(list 4800.125 870.3692) 
(list 4800.125 870.3794) 
(list 4800.125 870.3897) 
(list 4800.125 870.4) 
(list 4800 870.4)))
(apply 'command (append '("pline") coords '("c")))
(setq tap15 (ssadd (entlast) tap15))
(command "_mirror" (entlast) "" "4800,900" "4800,901" "No")
(setq tap15 (ssadd (entlast) tap15))
(setq coords (list 
(list 4800.5123 870.03) 
(list 4800.5016 870.03) 
(list 4800.5006 870.0403) 
(list 4800.4972 870.0506) 
(list 4800.4914 870.0608) 
(list 4800.4833 870.0711) 
(list 4800.4733 870.0814) 
(list 4800.4615 870.0917) 
(list 4800.4484 870.1019) 
(list 4800.4344 870.1122) 
(list 4800.4198 870.1225) 
(list 4800.4051 870.1328) 
(list 4800.3908 870.1431) 
(list 4800.3773 870.1533) 
(list 4800.365 870.1636) 
(list 4800.3543 870.1739) 
(list 4800.3456 870.1842) 
(list 4800.3391 870.1944) 
(list 4800.335 870.2047) 
(list 4800.3334 870.215) 
(list 4800.3345 870.2253) 
(list 4800.3383 870.2356) 
(list 4800.3445 870.2458) 
(list 4800.3531 870.2561) 
(list 4800.3638 870.2664) 
(list 4800.3763 870.2767) 
(list 4800.3902 870.2869) 
(list 4800.4051 870.2972) 
(list 4800.4206 870.3075) 
(list 4800.4362 870.3178) 
(list 4800.4513 870.3281) 
(list 4800.4656 870.3383) 
(list 4800.4787 870.3486) 
(list 4800.49 870.3589) 
(list 4800.4993 870.3692) 
(list 4800.5063 870.3794) 
(list 4800.5107 870.3897) 
(list 4800.5123 870.4) 
(list 4800.5123 870.4)))
(apply 'command (append '("pline") coords '("c")))
(setq tap15 (ssadd (entlast) tap15))
(command "_mirror" (entlast) "" "4800,900" "4800,901" "No")
(setq tap15 (ssadd (entlast) tap15))
(setq coords (list 
(list 4801.132 870.03) 
(list 4800.5123 870.03) 
(list 4800.5123 870.0403) 
(list 4800.5123 870.0506) 
(list 4800.5123 870.0608) 
(list 4800.5123 870.0711) 
(list 4800.5123 870.0814) 
(list 4800.5123 870.0917) 
(list 4800.5123 870.1019) 
(list 4800.5123 870.1122) 
(list 4800.5123 870.1225) 
(list 4800.5123 870.1328) 
(list 4800.5123 870.1431) 
(list 4800.5123 870.1533) 
(list 4800.5123 870.1636) 
(list 4800.5123 870.1739) 
(list 4800.5123 870.1842) 
(list 4800.5123 870.1944) 
(list 4800.5123 870.2047) 
(list 4800.5123 870.215) 
(list 4800.5123 870.2253) 
(list 4800.5123 870.2356) 
(list 4800.5123 870.2458) 
(list 4800.5123 870.2561) 
(list 4800.5123 870.2664) 
(list 4800.5123 870.2767) 
(list 4800.5123 870.2869) 
(list 4800.5123 870.2972) 
(list 4800.5123 870.3075) 
(list 4800.5123 870.3178) 
(list 4800.5123 870.3281) 
(list 4800.5123 870.3383) 
(list 4800.5123 870.3486) 
(list 4800.5123 870.3589) 
(list 4800.5123 870.3692) 
(list 4800.5123 870.3794) 
(list 4800.5123 870.3897) 
(list 4800.5123 870.4) 
(list 4801.132 870.4)))
(apply 'command (append '("pline") coords '("c")))
(setq tap15 (ssadd (entlast) tap15))
(command "_mirror" (entlast) "" "4800,900" "4800,901" "No")
(setq tap15 (ssadd (entlast) tap15))
(setq coords (list 
(list 4800 870.4) 
(list 4800.125 870.4) 
(list 4800.125 870.4103) 
(list 4800.125 870.4206) 
(list 4800.125 870.4308) 
(list 4800.125 870.4411) 
(list 4800.125 870.4514) 
(list 4800.125 870.4617) 
(list 4800.125 870.4719) 
(list 4800.125 870.4822) 
(list 4800.125 870.4925) 
(list 4800.125 870.5028) 
(list 4800.125 870.5131) 
(list 4800.125 870.5233) 
(list 4800.125 870.5336) 
(list 4800.125 870.5439) 
(list 4800.125 870.5542) 
(list 4800.125 870.5644) 
(list 4800.125 870.5747) 
(list 4800.125 870.585) 
(list 4800.125 870.5953) 
(list 4800.125 870.6056) 
(list 4800.125 870.6158) 
(list 4800.125 870.6261) 
(list 4800.125 870.6364) 
(list 4800.125 870.6467) 
(list 4800.125 870.6569) 
(list 4800.125 870.6672) 
(list 4800.125 870.6775) 
(list 4800.125 870.6878) 
(list 4800.125 870.6981) 
(list 4800.125 870.7083) 
(list 4800.125 870.7186) 
(list 4800.125 870.7289) 
(list 4800.125 870.7392) 
(list 4800.125 870.7494) 
(list 4800.125 870.7597) 
(list 4800.125 870.77) 
(list 4800 870.77)))
(apply 'command (append '("pline") coords '("c")))
(setq tap15 (ssadd (entlast) tap15))
(command "_mirror" (entlast) "" "4800,900" "4800,901" "No")
(setq tap15 (ssadd (entlast) tap15))
(setq coords (list 
(list 4800.5231 870.4) 
(list 4800.5123 870.4) 
(list 4800.5112 870.4103) 
(list 4800.5074 870.4206) 
(list 4800.5009 870.4308) 
(list 4800.4919 870.4411) 
(list 4800.4807 870.4514) 
(list 4800.4677 870.4617) 
(list 4800.4532 870.4719) 
(list 4800.4376 870.4822) 
(list 4800.4214 870.4925) 
(list 4800.4051 870.5028) 
(list 4800.3893 870.5131) 
(list 4800.3743 870.5233) 
(list 4800.3607 870.5336) 
(list 4800.3489 870.5439) 
(list 4800.3393 870.5542) 
(list 4800.3321 870.5644) 
(list 4800.3276 870.5747) 
(list 4800.3259 870.585) 
(list 4800.3272 870.5953) 
(list 4800.3313 870.6056) 
(list 4800.3382 870.6158) 
(list 4800.3477 870.6261) 
(list 4800.3596 870.6364) 
(list 4800.3734 870.6467) 
(list 4800.3887 870.6569) 
(list 4800.4051 870.6672) 
(list 4800.4222 870.6775) 
(list 4800.4393 870.6878) 
(list 4800.456 870.6981) 
(list 4800.4718 870.7083) 
(list 4800.4861 870.7186) 
(list 4800.4986 870.7289) 
(list 4800.5088 870.7392) 
(list 4800.5164 870.7494) 
(list 4800.5212 870.7597) 
(list 4800.5231 870.77) 
(list 4800.5231 870.77)))
(apply 'command (append '("pline") coords '("c")))
(setq tap15 (ssadd (entlast) tap15))
(command "_mirror" (entlast) "" "4800,900" "4800,901" "No")
(setq tap15 (ssadd (entlast) tap15))
(setq coords (list 
(list 4801.132 870.4) 
(list 4800.5231 870.4) 
(list 4800.5231 870.4103) 
(list 4800.5231 870.4206) 
(list 4800.5231 870.4308) 
(list 4800.5231 870.4411) 
(list 4800.5231 870.4514) 
(list 4800.5231 870.4617) 
(list 4800.5231 870.4719) 
(list 4800.5231 870.4822) 
(list 4800.5231 870.4925) 
(list 4800.5231 870.5028) 
(list 4800.5231 870.5131) 
(list 4800.5231 870.5233) 
(list 4800.5231 870.5336) 
(list 4800.5231 870.5439) 
(list 4800.5231 870.5542) 
(list 4800.5231 870.5644) 
(list 4800.5231 870.5747) 
(list 4800.5231 870.585) 
(list 4800.5231 870.5953) 
(list 4800.5231 870.6056) 
(list 4800.5231 870.6158) 
(list 4800.5231 870.6261) 
(list 4800.5231 870.6364) 
(list 4800.5231 870.6467) 
(list 4800.5231 870.6569) 
(list 4800.5231 870.6672) 
(list 4800.5231 870.6775) 
(list 4800.5231 870.6878) 
(list 4800.5231 870.6981) 
(list 4800.5231 870.7083) 
(list 4800.5231 870.7186) 
(list 4800.5231 870.7289) 
(list 4800.5231 870.7392) 
(list 4800.5231 870.7494) 
(list 4800.5231 870.7597) 
(list 4800.5231 870.77) 
(list 4801.132 870.77)))
(apply 'command (append '("pline") coords '("c")))
(setq tap15 (ssadd (entlast) tap15))
(command "_mirror" (entlast) "" "4800,900" "4800,901" "No")
(setq tap15 (ssadd (entlast) tap15))
(setq coords (list 
(list 4800 870.77) 
(list 4800.125 870.77) 
(list 4800.125 870.7803) 
(list 4800.125 870.7906) 
(list 4800.125 870.8008) 
(list 4800.125 870.8111) 
(list 4800.125 870.8214) 
(list 4800.125 870.8317) 
(list 4800.125 870.8419) 
(list 4800.125 870.8522) 
(list 4800.125 870.8625) 
(list 4800.125 870.8728) 
(list 4800.125 870.8831) 
(list 4800.125 870.8933) 
(list 4800.125 870.9036) 
(list 4800.125 870.9139) 
(list 4800.125 870.9242) 
(list 4800.125 870.9344) 
(list 4800.125 870.9447) 
(list 4800.125 870.955) 
(list 4800.125 870.9653) 
(list 4800.125 870.9756) 
(list 4800.125 870.9858) 
(list 4800.125 870.9961) 
(list 4800.125 871.0064) 
(list 4800.125 871.0167) 
(list 4800.125 871.0269) 
(list 4800.125 871.0372) 
(list 4800.125 871.0475) 
(list 4800.125 871.0578) 
(list 4800.125 871.0681) 
(list 4800.125 871.0783) 
(list 4800.125 871.0886) 
(list 4800.125 871.0989) 
(list 4800.125 871.1092) 
(list 4800.125 871.1194) 
(list 4800.125 871.1297) 
(list 4800.125 871.14) 
(list 4800 871.14)))
(apply 'command (append '("pline") coords '("c")))
(setq tap15 (ssadd (entlast) tap15))
(command "_mirror" (entlast) "" "4800,900" "4800,901" "No")
(setq tap15 (ssadd (entlast) tap15))
(setq coords (list 
(list 4800.5338 870.77) 
(list 4800.5231 870.77) 
(list 4800.5218 870.7803) 
(list 4800.5176 870.7906) 
(list 4800.5104 870.8008) 
(list 4800.5005 870.8111) 
(list 4800.4882 870.8214) 
(list 4800.4739 870.8317) 
(list 4800.4579 870.8419) 
(list 4800.4408 870.8522) 
(list 4800.423 870.8625) 
(list 4800.4052 870.8728) 
(list 4800.3878 870.8831) 
(list 4800.3714 870.8933) 
(list 4800.3565 870.9036) 
(list 4800.3435 870.9139) 
(list 4800.333 870.9242) 
(list 4800.3251 870.9344) 
(list 4800.3202 870.9447) 
(list 4800.3184 870.955) 
(list 4800.3198 870.9653) 
(list 4800.3243 870.9756) 
(list 4800.3319 870.9858) 
(list 4800.3423 870.9961) 
(list 4800.3553 871.0064) 
(list 4800.3704 871.0167) 
(list 4800.3872 871.0269) 
(list 4800.4052 871.0372) 
(list 4800.4238 871.0475) 
(list 4800.4425 871.0578) 
(list 4800.4608 871.0681) 
(list 4800.478 871.0783) 
(list 4800.4936 871.0886) 
(list 4800.5072 871.0989) 
(list 4800.5183 871.1092) 
(list 4800.5266 871.1194) 
(list 4800.5318 871.1297) 
(list 4800.5338 871.14) 
(list 4800.5338 871.14)))
(apply 'command (append '("pline") coords '("c")))
(setq tap15 (ssadd (entlast) tap15))
(command "_mirror" (entlast) "" "4800,900" "4800,901" "No")
(setq tap15 (ssadd (entlast) tap15))
(setq coords (list 
(list 4801.132 870.77) 
(list 4800.5338 870.77) 
(list 4800.5338 870.7803) 
(list 4800.5338 870.7906) 
(list 4800.5338 870.8008) 
(list 4800.5338 870.8111) 
(list 4800.5338 870.8214) 
(list 4800.5338 870.8317) 
(list 4800.5338 870.8419) 
(list 4800.5338 870.8522) 
(list 4800.5338 870.8625) 
(list 4800.5338 870.8728) 
(list 4800.5338 870.8831) 
(list 4800.5338 870.8933) 
(list 4800.5338 870.9036) 
(list 4800.5338 870.9139) 
(list 4800.5338 870.9242) 
(list 4800.5338 870.9344) 
(list 4800.5338 870.9447) 
(list 4800.5338 870.955) 
(list 4800.5338 870.9653) 
(list 4800.5338 870.9756) 
(list 4800.5338 870.9858) 
(list 4800.5338 870.9961) 
(list 4800.5338 871.0064) 
(list 4800.5338 871.0167) 
(list 4800.5338 871.0269) 
(list 4800.5338 871.0372) 
(list 4800.5338 871.0475) 
(list 4800.5338 871.0578) 
(list 4800.5338 871.0681) 
(list 4800.5338 871.0783) 
(list 4800.5338 871.0886) 
(list 4800.5338 871.0989) 
(list 4800.5338 871.1092) 
(list 4800.5338 871.1194) 
(list 4800.5338 871.1297) 
(list 4800.5338 871.14) 
(list 4801.132 871.14)))
(apply 'command (append '("pline") coords '("c")))
(setq tap15 (ssadd (entlast) tap15))
(command "_mirror" (entlast) "" "4800,900" "4800,901" "No")
(setq tap15 (ssadd (entlast) tap15))
(setq coords (list 
(list 4800 871.14) 
(list 4800.125 871.14) 
(list 4800.125 871.1503) 
(list 4800.125 871.1606) 
(list 4800.125 871.1708) 
(list 4800.125 871.1811) 
(list 4800.125 871.1914) 
(list 4800.125 871.2017) 
(list 4800.125 871.2119) 
(list 4800.125 871.2222) 
(list 4800.125 871.2325) 
(list 4800.125 871.2428) 
(list 4800.125 871.2531) 
(list 4800.125 871.2633) 
(list 4800.125 871.2736) 
(list 4800.125 871.2839) 
(list 4800.125 871.2942) 
(list 4800.125 871.3044) 
(list 4800.125 871.3147) 
(list 4800.125 871.325) 
(list 4800.125 871.3353) 
(list 4800.125 871.3456) 
(list 4800.125 871.3558) 
(list 4800.125 871.3661) 
(list 4800.125 871.3764) 
(list 4800.125 871.3867) 
(list 4800.125 871.3969) 
(list 4800.125 871.4072) 
(list 4800.125 871.4175) 
(list 4800.125 871.4278) 
(list 4800.125 871.4381) 
(list 4800.125 871.4483) 
(list 4800.125 871.4586) 
(list 4800.125 871.4689) 
(list 4800.125 871.4792) 
(list 4800.125 871.4894) 
(list 4800.125 871.4997) 
(list 4800.125 871.51) 
(list 4800 871.51)))
(apply 'command (append '("pline") coords '("c")))
(setq tap15 (ssadd (entlast) tap15))
(command "_mirror" (entlast) "" "4800,900" "4800,901" "No")
(setq tap15 (ssadd (entlast) tap15))
(setq coords (list 
(list 4800.5445 871.14) 
(list 4800.5338 871.14) 
(list 4800.5324 871.1503) 
(list 4800.5278 871.1606) 
(list 4800.5199 871.1708) 
(list 4800.5091 871.1811) 
(list 4800.4957 871.1914) 
(list 4800.48 871.2017) 
(list 4800.4626 871.2119) 
(list 4800.4439 871.2222) 
(list 4800.4246 871.2325) 
(list 4800.4052 871.2428) 
(list 4800.3862 871.2531) 
(list 4800.3684 871.2633) 
(list 4800.3522 871.2736) 
(list 4800.3381 871.2839) 
(list 4800.3267 871.2942) 
(list 4800.3181 871.3044) 
(list 4800.3128 871.3147) 
(list 4800.3108 871.325) 
(list 4800.3124 871.3353) 
(list 4800.3173 871.3456) 
(list 4800.3256 871.3558) 
(list 4800.3369 871.3661) 
(list 4800.351 871.3764) 
(list 4800.3674 871.3867) 
(list 4800.3857 871.3969) 
(list 4800.4052 871.4072) 
(list 4800.4254 871.4175) 
(list 4800.4457 871.4278) 
(list 4800.4655 871.4381) 
(list 4800.4841 871.4483) 
(list 4800.5011 871.4586) 
(list 4800.5158 871.4689) 
(list 4800.5278 871.4792) 
(list 4800.5368 871.4894) 
(list 4800.5424 871.4997) 
(list 4800.5445 871.51) 
(list 4800.5445 871.51)))
(apply 'command (append '("pline") coords '("c")))
(setq tap15 (ssadd (entlast) tap15))
(command "_mirror" (entlast) "" "4800,900" "4800,901" "No")
(setq tap15 (ssadd (entlast) tap15))
(setq coords (list 
(list 4801.132 871.14) 
(list 4800.5445 871.14) 
(list 4800.5445 871.1503) 
(list 4800.5445 871.1606) 
(list 4800.5445 871.1708) 
(list 4800.5445 871.1811) 
(list 4800.5445 871.1914) 
(list 4800.5445 871.2017) 
(list 4800.5445 871.2119) 
(list 4800.5445 871.2222) 
(list 4800.5445 871.2325) 
(list 4800.5445 871.2428) 
(list 4800.5445 871.2531) 
(list 4800.5445 871.2633) 
(list 4800.5445 871.2736) 
(list 4800.5445 871.2839) 
(list 4800.5445 871.2942) 
(list 4800.5445 871.3044) 
(list 4800.5445 871.3147) 
(list 4800.5445 871.325) 
(list 4800.5445 871.3353) 
(list 4800.5445 871.3456) 
(list 4800.5445 871.3558) 
(list 4800.5445 871.3661) 
(list 4800.5445 871.3764) 
(list 4800.5445 871.3867) 
(list 4800.5445 871.3969) 
(list 4800.5445 871.4072) 
(list 4800.5445 871.4175) 
(list 4800.5445 871.4278) 
(list 4800.5445 871.4381) 
(list 4800.5445 871.4483) 
(list 4800.5445 871.4586) 
(list 4800.5445 871.4689) 
(list 4800.5445 871.4792) 
(list 4800.5445 871.4894) 
(list 4800.5445 871.4997) 
(list 4800.5445 871.51) 
(list 4801.132 871.51)))
(apply 'command (append '("pline") coords '("c")))
(setq tap15 (ssadd (entlast) tap15))
(command "_mirror" (entlast) "" "4800,900" "4800,901" "No")
(setq tap15 (ssadd (entlast) tap15))
(setq coords (list 
(list 4800 871.51) 
(list 4800.125 871.51) 
(list 4800.125 871.5203) 
(list 4800.125 871.5306) 
(list 4800.125 871.5408) 
(list 4800.125 871.5511) 
(list 4800.125 871.5614) 
(list 4800.125 871.5717) 
(list 4800.125 871.5819) 
(list 4800.125 871.5922) 
(list 4800.125 871.6025) 
(list 4800.125 871.6128) 
(list 4800.125 871.6231) 
(list 4800.125 871.6333) 
(list 4800.125 871.6436) 
(list 4800.125 871.6539) 
(list 4800.125 871.6642) 
(list 4800.125 871.6744) 
(list 4800.125 871.6847) 
(list 4800.125 871.695) 
(list 4800.125 871.7053) 
(list 4800.125 871.7156) 
(list 4800.125 871.7258) 
(list 4800.125 871.7361) 
(list 4800.125 871.7464) 
(list 4800.125 871.7567) 
(list 4800.125 871.7669) 
(list 4800.125 871.7772) 
(list 4800.125 871.7875) 
(list 4800.125 871.7978) 
(list 4800.125 871.8081) 
(list 4800.125 871.8183) 
(list 4800.125 871.8286) 
(list 4800.125 871.8389) 
(list 4800.125 871.8492) 
(list 4800.125 871.8594) 
(list 4800.125 871.8697) 
(list 4800.125 871.88) 
(list 4800 871.88)))
(apply 'command (append '("pline") coords '("c")))
(setq tap15 (ssadd (entlast) tap15))
(command "_mirror" (entlast) "" "4800,900" "4800,901" "No")
(setq tap15 (ssadd (entlast) tap15))
(setq coords (list 
(list 4800.5553 871.51) 
(list 4800.5445 871.51) 
(list 4800.543 871.5203) 
(list 4800.5379 871.5306) 
(list 4800.5294 871.5408) 
(list 4800.5177 871.5511) 
(list 4800.5032 871.5614) 
(list 4800.4862 871.5717) 
(list 4800.4673 871.5819) 
(list 4800.4471 871.5922) 
(list 4800.4262 871.6025) 
(list 4800.4052 871.6128) 
(list 4800.3847 871.6231) 
(list 4800.3654 871.6333) 
(list 4800.3479 871.6436) 
(list 4800.3327 871.6539) 
(list 4800.3203 871.6642) 
(list 4800.3111 871.6744) 
(list 4800.3054 871.6847) 
(list 4800.3033 871.695) 
(list 4800.305 871.7053) 
(list 4800.3103 871.7156) 
(list 4800.3193 871.7258) 
(list 4800.3315 871.7361) 
(list 4800.3468 871.7464) 
(list 4800.3645 871.7567) 
(list 4800.3841 871.7669) 
(list 4800.4052 871.7772) 
(list 4800.427 871.7875) 
(list 4800.4489 871.7978) 
(list 4800.4702 871.8081) 
(list 4800.4903 871.8183) 
(list 4800.5086 871.8286) 
(list 4800.5244 871.8389) 
(list 4800.5373 871.8492) 
(list 4800.547 871.8594) 
(list 4800.553 871.8697) 
(list 4800.5553 871.88) 
(list 4800.5553 871.88)))
(apply 'command (append '("pline") coords '("c")))
(setq tap15 (ssadd (entlast) tap15))
(command "_mirror" (entlast) "" "4800,900" "4800,901" "No")
(setq tap15 (ssadd (entlast) tap15))
(setq coords (list 
(list 4801.132 871.51) 
(list 4800.5553 871.51) 
(list 4800.5553 871.5203) 
(list 4800.5553 871.5306) 
(list 4800.5553 871.5408) 
(list 4800.5553 871.5511) 
(list 4800.5553 871.5614) 
(list 4800.5553 871.5717) 
(list 4800.5553 871.5819) 
(list 4800.5553 871.5922) 
(list 4800.5553 871.6025) 
(list 4800.5553 871.6128) 
(list 4800.5553 871.6231) 
(list 4800.5553 871.6333) 
(list 4800.5553 871.6436) 
(list 4800.5553 871.6539) 
(list 4800.5553 871.6642) 
(list 4800.5553 871.6744) 
(list 4800.5553 871.6847) 
(list 4800.5553 871.695) 
(list 4800.5553 871.7053) 
(list 4800.5553 871.7156) 
(list 4800.5553 871.7258) 
(list 4800.5553 871.7361) 
(list 4800.5553 871.7464) 
(list 4800.5553 871.7567) 
(list 4800.5553 871.7669) 
(list 4800.5553 871.7772) 
(list 4800.5553 871.7875) 
(list 4800.5553 871.7978) 
(list 4800.5553 871.8081) 
(list 4800.5553 871.8183) 
(list 4800.5553 871.8286) 
(list 4800.5553 871.8389) 
(list 4800.5553 871.8492) 
(list 4800.5553 871.8594) 
(list 4800.5553 871.8697) 
(list 4800.5553 871.88) 
(list 4801.132 871.88)))
(apply 'command (append '("pline") coords '("c")))
(setq tap15 (ssadd (entlast) tap15))
(command "_mirror" (entlast) "" "4800,900" "4800,901" "No")
(setq tap15 (ssadd (entlast) tap15))
(setq coords (list 
(list 4800 871.88) 
(list 4800.125 871.88) 
(list 4800.125 871.8903) 
(list 4800.125 871.9006) 
(list 4800.125 871.9108) 
(list 4800.125 871.9211) 
(list 4800.125 871.9314) 
(list 4800.125 871.9417) 
(list 4800.125 871.9519) 
(list 4800.125 871.9622) 
(list 4800.125 871.9725) 
(list 4800.125 871.9828) 
(list 4800.125 871.9931) 
(list 4800.125 872.0033) 
(list 4800.125 872.0136) 
(list 4800.125 872.0239) 
(list 4800.125 872.0342) 
(list 4800.125 872.0444) 
(list 4800.125 872.0547) 
(list 4800.125 872.065) 
(list 4800.125 872.0753) 
(list 4800.125 872.0856) 
(list 4800.125 872.0958) 
(list 4800.125 872.1061) 
(list 4800.125 872.1164) 
(list 4800.125 872.1267) 
(list 4800.125 872.1369) 
(list 4800.125 872.1472) 
(list 4800.125 872.1575) 
(list 4800.125 872.1678) 
(list 4800.125 872.1781) 
(list 4800.125 872.1883) 
(list 4800.125 872.1986) 
(list 4800.125 872.2089) 
(list 4800.125 872.2192) 
(list 4800.125 872.2294) 
(list 4800.125 872.2397) 
(list 4800.125 872.25) 
(list 4800 872.25)))
(apply 'command (append '("pline") coords '("c")))
(setq tap15 (ssadd (entlast) tap15))
(command "_mirror" (entlast) "" "4800,900" "4800,901" "No")
(setq tap15 (ssadd (entlast) tap15))
(setq coords (list 
(list 4800.566 871.88) 
(list 4800.5553 871.88) 
(list 4800.5536 871.8903) 
(list 4800.5481 871.9006) 
(list 4800.5389 871.9108) 
(list 4800.5263 871.9211) 
(list 4800.5106 871.9314) 
(list 4800.4924 871.9417) 
(list 4800.4721 871.9519) 
(list 4800.4503 871.9622) 
(list 4800.4278 871.9725) 
(list 4800.4052 871.9828) 
(list 4800.3832 871.9931) 
(list 4800.3625 872.0033) 
(list 4800.3437 872.0136) 
(list 4800.3273 872.0239) 
(list 4800.314 872.0342) 
(list 4800.3041 872.0444) 
(list 4800.298 872.0547) 
(list 4800.2958 872.065) 
(list 4800.2976 872.0753) 
(list 4800.3034 872.0856) 
(list 4800.313 872.0958) 
(list 4800.3262 872.1061) 
(list 4800.3425 872.1164) 
(list 4800.3615 872.1267) 
(list 4800.3826 872.1369) 
(list 4800.4052 872.1472) 
(list 4800.4286 872.1575) 
(list 4800.4521 872.1678) 
(list 4800.4749 872.1781) 
(list 4800.4965 872.1883) 
(list 4800.516 872.1986) 
(list 4800.533 872.2089) 
(list 4800.5469 872.2192) 
(list 4800.5572 872.2294) 
(list 4800.5636 872.2397) 
(list 4800.566 872.25) 
(list 4800.566 872.25)))
(apply 'command (append '("pline") coords '("c")))
(setq tap15 (ssadd (entlast) tap15))
(command "_mirror" (entlast) "" "4800,900" "4800,901" "No")
(setq tap15 (ssadd (entlast) tap15))
(setq coords (list 
(list 4801.132 871.88) 
(list 4800.566 871.88) 
(list 4800.566 871.8903) 
(list 4800.566 871.9006) 
(list 4800.566 871.9108) 
(list 4800.566 871.9211) 
(list 4800.566 871.9314) 
(list 4800.566 871.9417) 
(list 4800.566 871.9519) 
(list 4800.566 871.9622) 
(list 4800.566 871.9725) 
(list 4800.566 871.9828) 
(list 4800.566 871.9931) 
(list 4800.566 872.0033) 
(list 4800.566 872.0136) 
(list 4800.566 872.0239) 
(list 4800.566 872.0342) 
(list 4800.566 872.0444) 
(list 4800.566 872.0547) 
(list 4800.566 872.065) 
(list 4800.566 872.0753) 
(list 4800.566 872.0856) 
(list 4800.566 872.0958) 
(list 4800.566 872.1061) 
(list 4800.566 872.1164) 
(list 4800.566 872.1267) 
(list 4800.566 872.1369) 
(list 4800.566 872.1472) 
(list 4800.566 872.1575) 
(list 4800.566 872.1678) 
(list 4800.566 872.1781) 
(list 4800.566 872.1883) 
(list 4800.566 872.1986) 
(list 4800.566 872.2089) 
(list 4800.566 872.2192) 
(list 4800.566 872.2294) 
(list 4800.566 872.2397) 
(list 4800.566 872.25) 
(list 4801.132 872.25)))
(apply 'command (append '("pline") coords '("c")))
(setq tap15 (ssadd (entlast) tap15))
(command "_mirror" (entlast) "" "4800,900" "4800,901" "No")
(setq tap15 (ssadd (entlast) tap15))
(command "_block" "blktap15" "4800,900" tap15 "")
(command "_insert" "blktap15" "4800,900" "1" "1" "0")
(command "_insert" "blktap15" "4800,900" "1" "1" "180")
(setq uc15 nil)
(setq uc15 (ssadd))
(setq coords (list 
(list 0 -0.185) 
(list 0.125 -0.185) 
(list 0.125 -0.17472) 
(list 0.125 -0.16444) 
(list 0.125 -0.15417) 
(list 0.125 -0.14389) 
(list 0.125 -0.13361) 
(list 0.125 -0.12333) 
(list 0.125 -0.11306) 
(list 0.125 -0.10278) 
(list 0.125 -0.0925) 
(list 0.125 -0.082222) 
(list 0.125 -0.071944) 
(list 0.125 -0.061667) 
(list 0.125 -0.051389) 
(list 0.125 -0.041111) 
(list 0.125 -0.030833) 
(list 0.125 -0.020556) 
(list 0.125 -0.010278) 
(list 0.125 0) 
(list 0.125 0.010278) 
(list 0.125 0.020556) 
(list 0.125 0.030833) 
(list 0.125 0.041111) 
(list 0.125 0.051389) 
(list 0.125 0.061667) 
(list 0.125 0.071944) 
(list 0.125 0.082222) 
(list 0.125 0.0925) 
(list 0.125 0.10278) 
(list 0.125 0.11306) 
(list 0.125 0.12333) 
(list 0.125 0.13361) 
(list 0.125 0.14389) 
(list 0.125 0.15417) 
(list 0.125 0.16444) 
(list 0.125 0.17472) 
(list 0.125 0.185) 
(list 0 0.185)))
(apply 'command (append '("pline") coords '("c")))
(setq uc15 (ssadd (entlast) uc15))
(setq coords (list 
(list 1.132 -0.185) 
(list 0.566 -0.185) 
(list 0.56392 -0.17472) 
(list 0.55774 -0.16444) 
(list 0.54765 -0.15417) 
(list 0.53395 -0.14389) 
(list 0.51706 -0.13361) 
(list 0.4975 -0.12333) 
(list 0.47586 -0.11306) 
(list 0.45279 -0.10278) 
(list 0.429 -0.0925) 
(list 0.40521 -0.082222) 
(list 0.38214 -0.071944) 
(list 0.3605 -0.061667) 
(list 0.34094 -0.051389) 
(list 0.32405 -0.041111) 
(list 0.31035 -0.030833) 
(list 0.30026 -0.020556) 
(list 0.29408 -0.010278) 
(list 0.292 0) 
(list 0.29408 0.010278) 
(list 0.30026 0.020556) 
(list 0.31035 0.030833) 
(list 0.32405 0.041111) 
(list 0.34094 0.051389) 
(list 0.3605 0.061667) 
(list 0.38214 0.071944) 
(list 0.40521 0.082222) 
(list 0.429 0.0925) 
(list 0.45279 0.10278) 
(list 0.47586 0.11306) 
(list 0.4975 0.12333) 
(list 0.51706 0.13361) 
(list 0.53395 0.14389) 
(list 0.54765 0.15417) 
(list 0.55774 0.16444) 
(list 0.56392 0.17472) 
(list 0.566 0.185) 
(list 1.132 0.185)))
(apply 'command (append '("pline") coords '("c")))
(setq uc15 (ssadd (entlast) uc15))
(command "_block" "blkuc15" "0,0.185" uc15 "")
(command "_insert" "blkuc15" "4800,872.62" "1" "1" "0")
(command "_insert" "blkuc15" "4800,872.25" "1" "1" "180")
(command "_insert" "blkuc15" "4800,872.99" "1" "1" "0")
(command "_insert" "blkuc15" "4800,872.62" "1" "1" "180")
(command "_insert" "blkuc15" "4800,873.36" "1" "1" "0")
(command "_insert" "blkuc15" "4800,872.99" "1" "1" "180")
(command "_insert" "blkuc15" "4800,873.73" "1" "1" "0")
(command "_insert" "blkuc15" "4800,873.36" "1" "1" "180")
(command "_insert" "blkuc15" "4800,874.1" "1" "1" "0")
(command "_insert" "blkuc15" "4800,873.73" "1" "1" "180")
(command "_insert" "blkuc15" "4800,874.47" "1" "1" "0")
(command "_insert" "blkuc15" "4800,874.1" "1" "1" "180")
(command "_insert" "blkuc15" "4800,874.84" "1" "1" "0")
(command "_insert" "blkuc15" "4800,874.47" "1" "1" "180")
(command "_insert" "blkuc15" "4800,875.21" "1" "1" "0")
(command "_insert" "blkuc15" "4800,874.84" "1" "1" "180")
(command "_insert" "blkuc15" "4800,875.58" "1" "1" "0")
(command "_insert" "blkuc15" "4800,875.21" "1" "1" "180")
(command "_insert" "blkuc15" "4800,875.95" "1" "1" "0")
(command "_insert" "blkuc15" "4800,875.58" "1" "1" "180")
(command "_insert" "blkuc15" "4800,876.32" "1" "1" "0")
(command "_insert" "blkuc15" "4800,875.95" "1" "1" "180")
(command "_insert" "blkuc15" "4800,876.69" "1" "1" "0")
(command "_insert" "blkuc15" "4800,876.32" "1" "1" "180")
(command "_insert" "blkuc15" "4800,877.06" "1" "1" "0")
(command "_insert" "blkuc15" "4800,876.69" "1" "1" "180")
(command "_insert" "blkuc15" "4800,877.43" "1" "1" "0")
(command "_insert" "blkuc15" "4800,877.06" "1" "1" "180")
(command "_insert" "blkuc15" "4800,877.8" "1" "1" "0")
(command "_insert" "blkuc15" "4800,877.43" "1" "1" "180")
(command "_insert" "blkuc15" "4800,878.17" "1" "1" "0")
(command "_insert" "blkuc15" "4800,877.8" "1" "1" "180")
(command "_insert" "blkuc15" "4800,878.54" "1" "1" "0")
(command "_insert" "blkuc15" "4800,878.17" "1" "1" "180")
(command "_insert" "blkuc15" "4800,878.91" "1" "1" "0")
(command "_insert" "blkuc15" "4800,878.54" "1" "1" "180")
(command "_insert" "blkuc15" "4800,879.28" "1" "1" "0")
(command "_insert" "blkuc15" "4800,878.91" "1" "1" "180")
(command "_insert" "blkuc15" "4800,879.65" "1" "1" "0")
(command "_insert" "blkuc15" "4800,879.28" "1" "1" "180")
(command "_insert" "blkuc15" "4800,880.02" "1" "1" "0")
(command "_insert" "blkuc15" "4800,879.65" "1" "1" "180")
(command "_insert" "blkuc15" "4800,880.39" "1" "1" "0")
(command "_insert" "blkuc15" "4800,880.02" "1" "1" "180")
(command "_insert" "blkuc15" "4800,880.76" "1" "1" "0")
(command "_insert" "blkuc15" "4800,880.39" "1" "1" "180")
(command "_insert" "blkuc15" "4800,881.13" "1" "1" "0")
(command "_insert" "blkuc15" "4800,880.76" "1" "1" "180")
(command "_insert" "blkuc15" "4800,881.5" "1" "1" "0")
(command "_insert" "blkuc15" "4800,881.13" "1" "1" "180")
(command "_insert" "blkuc15" "4800,881.87" "1" "1" "0")
(command "_insert" "blkuc15" "4800,881.5" "1" "1" "180")
(command "_insert" "blkuc15" "4800,882.24" "1" "1" "0")
(command "_insert" "blkuc15" "4800,881.87" "1" "1" "180")
(command "_insert" "blkuc15" "4800,882.61" "1" "1" "0")
(command "_insert" "blkuc15" "4800,882.24" "1" "1" "180")
(command "_insert" "blkuc15" "4800,882.98" "1" "1" "0")
(command "_insert" "blkuc15" "4800,882.61" "1" "1" "180")
(command "_insert" "blkuc15" "4800,883.35" "1" "1" "0")
(command "_insert" "blkuc15" "4800,882.98" "1" "1" "180")
(command "_insert" "blkuc15" "4800,883.72" "1" "1" "0")
(command "_insert" "blkuc15" "4800,883.35" "1" "1" "180")
(command "_insert" "blkuc15" "4800,884.09" "1" "1" "0")
(command "_insert" "blkuc15" "4800,883.72" "1" "1" "180")
(command "_insert" "blkuc15" "4800,884.46" "1" "1" "0")
(command "_insert" "blkuc15" "4800,884.09" "1" "1" "180")
(command "_insert" "blkuc15" "4800,884.83" "1" "1" "0")
(command "_insert" "blkuc15" "4800,884.46" "1" "1" "180")
(command "_insert" "blkuc15" "4800,885.2" "1" "1" "0")
(command "_insert" "blkuc15" "4800,884.83" "1" "1" "180")
(command "_insert" "blkuc15" "4800,885.57" "1" "1" "0")
(command "_insert" "blkuc15" "4800,885.2" "1" "1" "180")
(command "_insert" "blkuc15" "4800,885.94" "1" "1" "0")
(command "_insert" "blkuc15" "4800,885.57" "1" "1" "180")
(command "_insert" "blkuc15" "4800,886.31" "1" "1" "0")
(command "_insert" "blkuc15" "4800,885.94" "1" "1" "180")
(command "_insert" "blkuc15" "4800,886.68" "1" "1" "0")
(command "_insert" "blkuc15" "4800,886.31" "1" "1" "180")
(command "_insert" "blkuc15" "4800,887.05" "1" "1" "0")
(command "_insert" "blkuc15" "4800,886.68" "1" "1" "180")
(command "_insert" "blkuc15" "4800,887.42" "1" "1" "0")
(command "_insert" "blkuc15" "4800,887.05" "1" "1" "180")
(command "_insert" "blkuc15" "4800,887.79" "1" "1" "0")
(command "_insert" "blkuc15" "4800,887.42" "1" "1" "180")
(command "_insert" "blkuc15" "4800,888.16" "1" "1" "0")
(command "_insert" "blkuc15" "4800,887.79" "1" "1" "180")
(command "_insert" "blkuc15" "4800,888.53" "1" "1" "0")
(command "_insert" "blkuc15" "4800,888.16" "1" "1" "180")
(command "_insert" "blkuc15" "4800,888.9" "1" "1" "0")
(command "_insert" "blkuc15" "4800,888.53" "1" "1" "180")
(command "_insert" "blkuc15" "4800,889.27" "1" "1" "0")
(command "_insert" "blkuc15" "4800,888.9" "1" "1" "180")
(command "_insert" "blkuc15" "4800,889.64" "1" "1" "0")
(command "_insert" "blkuc15" "4800,889.27" "1" "1" "180")
(command "_insert" "blkuc15" "4800,890.01" "1" "1" "0")
(command "_insert" "blkuc15" "4800,889.64" "1" "1" "180")
(command "_insert" "blkuc15" "4800,890.38" "1" "1" "0")
(command "_insert" "blkuc15" "4800,890.01" "1" "1" "180")
(command "_insert" "blkuc15" "4800,890.75" "1" "1" "0")
(command "_insert" "blkuc15" "4800,890.38" "1" "1" "180")
(command "_insert" "blkuc15" "4800,891.12" "1" "1" "0")
(command "_insert" "blkuc15" "4800,890.75" "1" "1" "180")
(command "_insert" "blkuc15" "4800,891.49" "1" "1" "0")
(command "_insert" "blkuc15" "4800,891.12" "1" "1" "180")
(command "_insert" "blkuc15" "4800,891.86" "1" "1" "0")
(command "_insert" "blkuc15" "4800,891.49" "1" "1" "180")
(command "_insert" "blkuc15" "4800,892.23" "1" "1" "0")
(command "_insert" "blkuc15" "4800,891.86" "1" "1" "180")
(command "_insert" "blkuc15" "4800,892.6" "1" "1" "0")
(command "_insert" "blkuc15" "4800,892.23" "1" "1" "180")
(command "_insert" "blkuc15" "4800,892.97" "1" "1" "0")
(command "_insert" "blkuc15" "4800,892.6" "1" "1" "180")
(command "_insert" "blkuc15" "4800,893.34" "1" "1" "0")
(command "_insert" "blkuc15" "4800,892.97" "1" "1" "180")
(command "_insert" "blkuc15" "4800,893.71" "1" "1" "0")
(command "_insert" "blkuc15" "4800,893.34" "1" "1" "180")
(command "_insert" "blkuc15" "4800,894.08" "1" "1" "0")
(command "_insert" "blkuc15" "4800,893.71" "1" "1" "180")
(command "_insert" "blkuc15" "4800,894.45" "1" "1" "0")
(command "_insert" "blkuc15" "4800,894.08" "1" "1" "180")
(command "_insert" "blkuc15" "4800,894.82" "1" "1" "0")
(command "_insert" "blkuc15" "4800,894.45" "1" "1" "180")
(command "_insert" "blkuc15" "4800,895.19" "1" "1" "0")
(command "_insert" "blkuc15" "4800,894.82" "1" "1" "180")
(command "_insert" "blkuc15" "4800,895.56" "1" "1" "0")
(command "_insert" "blkuc15" "4800,895.19" "1" "1" "180")
(command "_insert" "blkuc15" "4800,895.93" "1" "1" "0")
(command "_insert" "blkuc15" "4800,895.56" "1" "1" "180")
(command "_insert" "blkuc15" "4800,896.3" "1" "1" "0")
(command "_insert" "blkuc15" "4800,895.93" "1" "1" "180")
(command "_insert" "blkuc15" "4800,896.67" "1" "1" "0")
(command "_insert" "blkuc15" "4800,896.3" "1" "1" "180")
(command "_insert" "blkuc15" "4800,897.04" "1" "1" "0")
(command "_insert" "blkuc15" "4800,896.67" "1" "1" "180")
(command "_insert" "blkuc15" "4800,897.41" "1" "1" "0")
(command "_insert" "blkuc15" "4800,897.04" "1" "1" "180")
(command "_insert" "blkuc15" "4800,897.78" "1" "1" "0")
(command "_insert" "blkuc15" "4800,897.41" "1" "1" "180")
(command "_insert" "blkuc15" "4800,898.15" "1" "1" "0")
(command "_insert" "blkuc15" "4800,897.78" "1" "1" "180")
(command "_insert" "blkuc15" "4800,898.52" "1" "1" "0")
(command "_insert" "blkuc15" "4800,898.15" "1" "1" "180")
(command "_insert" "blkuc15" "4800,898.89" "1" "1" "0")
(command "_insert" "blkuc15" "4800,898.52" "1" "1" "180")
(command "_insert" "blkuc15" "4800,899.26" "1" "1" "0")
(command "_insert" "blkuc15" "4800,898.89" "1" "1" "180")
(command "_insert" "blkuc15" "4800,899.63" "1" "1" "0")
(command "_insert" "blkuc15" "4800,899.26" "1" "1" "180")
(command "_insert" "blkuc15" "4800,900" "1" "1" "0")
(command "_insert" "blkuc15" "4800,899.63" "1" "1" "180")
(command "_insert" "blkuc15" "4800,900.37" "1" "1" "0")
(command "_insert" "blkuc15" "4800,900" "1" "1" "180")
(command "_insert" "blkuc15" "4800,900.74" "1" "1" "0")
(command "_insert" "blkuc15" "4800,900.37" "1" "1" "180")
(command "_insert" "blkuc15" "4800,901.11" "1" "1" "0")
(command "_insert" "blkuc15" "4800,900.74" "1" "1" "180")
(command "_insert" "blkuc15" "4800,901.48" "1" "1" "0")
(command "_insert" "blkuc15" "4800,901.11" "1" "1" "180")
(command "_insert" "blkuc15" "4800,901.85" "1" "1" "0")
(command "_insert" "blkuc15" "4800,901.48" "1" "1" "180")
(command "_insert" "blkuc15" "4800,902.22" "1" "1" "0")
(command "_insert" "blkuc15" "4800,901.85" "1" "1" "180")
(command "_insert" "blkuc15" "4800,902.59" "1" "1" "0")
(command "_insert" "blkuc15" "4800,902.22" "1" "1" "180")
(command "_insert" "blkuc15" "4800,902.96" "1" "1" "0")
(command "_insert" "blkuc15" "4800,902.59" "1" "1" "180")
(command "_insert" "blkuc15" "4800,903.33" "1" "1" "0")
(command "_insert" "blkuc15" "4800,902.96" "1" "1" "180")
(command "_insert" "blkuc15" "4800,903.7" "1" "1" "0")
(command "_insert" "blkuc15" "4800,903.33" "1" "1" "180")
(command "_insert" "blkuc15" "4800,904.07" "1" "1" "0")
(command "_insert" "blkuc15" "4800,903.7" "1" "1" "180")
(command "_insert" "blkuc15" "4800,904.44" "1" "1" "0")
(command "_insert" "blkuc15" "4800,904.07" "1" "1" "180")
(command "_insert" "blkuc15" "4800,904.81" "1" "1" "0")
(command "_insert" "blkuc15" "4800,904.44" "1" "1" "180")
(command "_insert" "blkuc15" "4800,905.18" "1" "1" "0")
(command "_insert" "blkuc15" "4800,904.81" "1" "1" "180")
(command "_insert" "blkuc15" "4800,905.55" "1" "1" "0")
(command "_insert" "blkuc15" "4800,905.18" "1" "1" "180")
(command "_insert" "blkuc15" "4800,905.92" "1" "1" "0")
(command "_insert" "blkuc15" "4800,905.55" "1" "1" "180")
(command "_insert" "blkuc15" "4800,906.29" "1" "1" "0")
(command "_insert" "blkuc15" "4800,905.92" "1" "1" "180")
(command "_insert" "blkuc15" "4800,906.66" "1" "1" "0")
(command "_insert" "blkuc15" "4800,906.29" "1" "1" "180")
(command "_insert" "blkuc15" "4800,907.03" "1" "1" "0")
(command "_insert" "blkuc15" "4800,906.66" "1" "1" "180")
(command "_insert" "blkuc15" "4800,907.4" "1" "1" "0")
(command "_insert" "blkuc15" "4800,907.03" "1" "1" "180")
(command "_insert" "blkuc15" "4800,907.77" "1" "1" "0")
(command "_insert" "blkuc15" "4800,907.4" "1" "1" "180")
(command "_insert" "blkuc15" "4800,908.14" "1" "1" "0")
(command "_insert" "blkuc15" "4800,907.77" "1" "1" "180")
(command "_insert" "blkuc15" "4800,908.51" "1" "1" "0")
(command "_insert" "blkuc15" "4800,908.14" "1" "1" "180")
(command "_insert" "blkuc15" "4800,908.88" "1" "1" "0")
(command "_insert" "blkuc15" "4800,908.51" "1" "1" "180")
(command "_insert" "blkuc15" "4800,909.25" "1" "1" "0")
(command "_insert" "blkuc15" "4800,908.88" "1" "1" "180")
(command "_insert" "blkuc15" "4800,909.62" "1" "1" "0")
(command "_insert" "blkuc15" "4800,909.25" "1" "1" "180")
(command "_insert" "blkuc15" "4800,909.99" "1" "1" "0")
(command "_insert" "blkuc15" "4800,909.62" "1" "1" "180")
(command "_insert" "blkuc15" "4800,910.36" "1" "1" "0")
(command "_insert" "blkuc15" "4800,909.99" "1" "1" "180")
(command "_insert" "blkuc15" "4800,910.73" "1" "1" "0")
(command "_insert" "blkuc15" "4800,910.36" "1" "1" "180")
(command "_insert" "blkuc15" "4800,911.1" "1" "1" "0")
(command "_insert" "blkuc15" "4800,910.73" "1" "1" "180")
(command "_insert" "blkuc15" "4800,911.47" "1" "1" "0")
(command "_insert" "blkuc15" "4800,911.1" "1" "1" "180")
(command "_insert" "blkuc15" "4800,911.84" "1" "1" "0")
(command "_insert" "blkuc15" "4800,911.47" "1" "1" "180")
(command "_insert" "blkuc15" "4800,912.21" "1" "1" "0")
(command "_insert" "blkuc15" "4800,911.84" "1" "1" "180")
(command "_insert" "blkuc15" "4800,912.58" "1" "1" "0")
(command "_insert" "blkuc15" "4800,912.21" "1" "1" "180")
(command "_insert" "blkuc15" "4800,912.95" "1" "1" "0")
(command "_insert" "blkuc15" "4800,912.58" "1" "1" "180")
(command "_insert" "blkuc15" "4800,913.32" "1" "1" "0")
(command "_insert" "blkuc15" "4800,912.95" "1" "1" "180")
(command "_insert" "blkuc15" "4800,913.69" "1" "1" "0")
(command "_insert" "blkuc15" "4800,913.32" "1" "1" "180")
(command "_insert" "blkuc15" "4800,914.06" "1" "1" "0")
(command "_insert" "blkuc15" "4800,913.69" "1" "1" "180")
(command "_insert" "blkuc15" "4800,914.43" "1" "1" "0")
(command "_insert" "blkuc15" "4800,914.06" "1" "1" "180")
(command "_insert" "blkuc15" "4800,914.8" "1" "1" "0")
(command "_insert" "blkuc15" "4800,914.43" "1" "1" "180")
(command "_insert" "blkuc15" "4800,915.17" "1" "1" "0")
(command "_insert" "blkuc15" "4800,914.8" "1" "1" "180")
(command "_insert" "blkuc15" "4800,915.54" "1" "1" "0")
(command "_insert" "blkuc15" "4800,915.17" "1" "1" "180")
(command "_insert" "blkuc15" "4800,915.91" "1" "1" "0")
(command "_insert" "blkuc15" "4800,915.54" "1" "1" "180")
(command "_insert" "blkuc15" "4800,916.28" "1" "1" "0")
(command "_insert" "blkuc15" "4800,915.91" "1" "1" "180")
(command "_insert" "blkuc15" "4800,916.65" "1" "1" "0")
(command "_insert" "blkuc15" "4800,916.28" "1" "1" "180")
(command "_insert" "blkuc15" "4800,917.02" "1" "1" "0")
(command "_insert" "blkuc15" "4800,916.65" "1" "1" "180")
(command "_insert" "blkuc15" "4800,917.39" "1" "1" "0")
(command "_insert" "blkuc15" "4800,917.02" "1" "1" "180")
(command "_insert" "blkuc15" "4800,917.76" "1" "1" "0")
(command "_insert" "blkuc15" "4800,917.39" "1" "1" "180")
(command "_insert" "blkuc15" "4800,918.13" "1" "1" "0")
(command "_insert" "blkuc15" "4800,917.76" "1" "1" "180")
(command "_insert" "blkuc15" "4800,918.5" "1" "1" "0")
(command "_insert" "blkuc15" "4800,918.13" "1" "1" "180")
(command "_insert" "blkuc15" "4800,918.87" "1" "1" "0")
(command "_insert" "blkuc15" "4800,918.5" "1" "1" "180")
(command "_insert" "blkuc15" "4800,919.24" "1" "1" "0")
(command "_insert" "blkuc15" "4800,918.87" "1" "1" "180")
(command "_insert" "blkuc15" "4800,919.61" "1" "1" "0")
(command "_insert" "blkuc15" "4800,919.24" "1" "1" "180")
(command "_insert" "blkuc15" "4800,919.98" "1" "1" "0")
(command "_insert" "blkuc15" "4800,919.61" "1" "1" "180")
(command "_insert" "blkuc15" "4800,920.35" "1" "1" "0")
(command "_insert" "blkuc15" "4800,919.98" "1" "1" "180")
(command "_insert" "blkuc15" "4800,920.72" "1" "1" "0")
(command "_insert" "blkuc15" "4800,920.35" "1" "1" "180")
(command "_insert" "blkuc15" "4800,921.09" "1" "1" "0")
(command "_insert" "blkuc15" "4800,920.72" "1" "1" "180")
(command "_insert" "blkuc15" "4800,921.46" "1" "1" "0")
(command "_insert" "blkuc15" "4800,921.09" "1" "1" "180")
(command "_insert" "blkuc15" "4800,921.83" "1" "1" "0")
(command "_insert" "blkuc15" "4800,921.46" "1" "1" "180")
(command "_insert" "blkuc15" "4800,922.2" "1" "1" "0")
(command "_insert" "blkuc15" "4800,921.83" "1" "1" "180")
(command "_insert" "blkuc15" "4800,922.57" "1" "1" "0")
(command "_insert" "blkuc15" "4800,922.2" "1" "1" "180")
(command "_insert" "blkuc15" "4800,922.94" "1" "1" "0")
(command "_insert" "blkuc15" "4800,922.57" "1" "1" "180")
(command "_insert" "blkuc15" "4800,923.31" "1" "1" "0")
(command "_insert" "blkuc15" "4800,922.94" "1" "1" "180")
(command "_insert" "blkuc15" "4800,923.68" "1" "1" "0")
(command "_insert" "blkuc15" "4800,923.31" "1" "1" "180")
(command "_insert" "blkuc15" "4800,924.05" "1" "1" "0")
(command "_insert" "blkuc15" "4800,923.68" "1" "1" "180")
(command "_insert" "blkuc15" "4800,924.42" "1" "1" "0")
(command "_insert" "blkuc15" "4800,924.05" "1" "1" "180")
(command "_insert" "blkuc15" "4800,924.79" "1" "1" "0")
(command "_insert" "blkuc15" "4800,924.42" "1" "1" "180")
(command "_insert" "blkuc15" "4800,925.16" "1" "1" "0")
(command "_insert" "blkuc15" "4800,924.79" "1" "1" "180")
(command "_insert" "blkuc15" "4800,925.53" "1" "1" "0")
(command "_insert" "blkuc15" "4800,925.16" "1" "1" "180")
(command "_insert" "blkuc15" "4800,925.9" "1" "1" "0")
(command "_insert" "blkuc15" "4800,925.53" "1" "1" "180")
(command "_insert" "blkuc15" "4800,926.27" "1" "1" "0")
(command "_insert" "blkuc15" "4800,925.9" "1" "1" "180")
(command "_insert" "blkuc15" "4800,926.64" "1" "1" "0")
(command "_insert" "blkuc15" "4800,926.27" "1" "1" "180")
(command "_insert" "blkuc15" "4800,927.01" "1" "1" "0")
(command "_insert" "blkuc15" "4800,926.64" "1" "1" "180")
(command "_insert" "blkuc15" "4800,927.38" "1" "1" "0")
(command "_insert" "blkuc15" "4800,927.01" "1" "1" "180")
(command "_insert" "blkuc15" "4800,927.75" "1" "1" "0")
(command "_insert" "blkuc15" "4800,927.38" "1" "1" "180")
(command "_layer" "set" "phccover" "")
(command "_rectangle" "4798.868,933.3" "4801.132,866.7")
(command "_layer" "set" "nitride" "")
(setq phc15 currobj)
(command "_layer" "set" "cover" "")
(command "_rectangle" "4798.868,836.7" "4801.132,963.3")
(command "_layer" "set" "nitride" "")
(command "_layer" "set" "text" "")
(command "_circle" "4797.918,846.7" "0.075")
(command "_circle" "4797.543,846.7" "0.15")
(command "_circle" "4797.168,846.7" "0.075")
(command "_circle" "4796.793,846.7" "0.15")
(command "_circle" "4797.918,848.7" "0.075")
(command "_circle" "4797.543,848.7" "0.075")
(command "_circle" "4797.168,848.7" "0.15")
(command "_circle" "4796.793,848.7" "0.15")
(command "_circle" "4797.918,850.7" "0.075")
(command "_circle" "4797.543,850.7" "0.15")
(command "_circle" "4797.168,850.7" "0.15")
(command "_circle" "4796.793,850.7" "0.15")
(command "_circle" "4797.918,852.7" "0.075")
(command "_circle" "4797.543,852.7" "0.075")
(command "_circle" "4797.168,852.7" "0.075")
(command "_circle" "4796.793,852.7" "0.075")
(command "_circle" "4796.418,852.7" "0.15")
(command "_circle" "4797.918,854.7" "0.075")
(command "_circle" "4797.543,854.7" "0.15")
(command "_circle" "4797.168,854.7" "0.075")
(command "_circle" "4796.793,854.7" "0.075")
(command "_circle" "4796.418,854.7" "0.15")
(command "_circle" "4797.918,856.7" "0.075")
(command "_circle" "4797.543,856.7" "0.075")
(command "_circle" "4797.168,856.7" "0.15")
(command "_circle" "4796.793,856.7" "0.075")
(command "_circle" "4796.418,856.7" "0.15")
(command "_circle" "4797.918,858.7" "0.075")
(command "_circle" "4797.543,858.7" "0.15")
(command "_circle" "4797.168,858.7" "0.15")
(command "_circle" "4796.793,858.7" "0.075")
(command "_circle" "4796.418,858.7" "0.15")
(command "_circle" "4797.918,860.7" "0.075")
(command "_circle" "4797.543,860.7" "0.075")
(command "_circle" "4797.168,860.7" "0.075")
(command "_circle" "4796.793,860.7" "0.15")
(command "_circle" "4796.418,860.7" "0.15")
(command "_circle" "4797.918,862.7" "0.075")
(command "_circle" "4797.543,862.7" "0.15")
(command "_circle" "4797.168,862.7" "0.075")
(command "_circle" "4796.793,862.7" "0.15")
(command "_circle" "4796.418,862.7" "0.15")
(command "_circle" "4797.918,864.7" "0.075")
(command "_circle" "4797.543,864.7" "0.075")
(command "_circle" "4797.168,864.7" "0.15")
(command "_circle" "4796.793,864.7" "0.15")
(command "_circle" "4796.418,864.7" "0.15")
(command "_circle" "4797.918,866.7" "0.075")
(command "_circle" "4797.543,866.7" "0.15")
(command "_circle" "4797.168,866.7" "0.15")
(command "_circle" "4796.793,866.7" "0.15")
(command "_circle" "4796.418,866.7" "0.15")
(command "_circle" "4797.918,868.7" "0.075")
(command "_circle" "4797.543,868.7" "0.075")
(command "_circle" "4797.168,868.7" "0.075")
(command "_circle" "4796.793,868.7" "0.075")
(command "_circle" "4796.418,868.7" "0.075")
(command "_circle" "4796.043,868.7" "0.15")
(command "_circle" "4797.918,870.7" "0.075")
(command "_circle" "4797.543,870.7" "0.15")
(command "_circle" "4797.168,870.7" "0.075")
(command "_circle" "4796.793,870.7" "0.075")
(command "_circle" "4796.418,870.7" "0.075")
(command "_circle" "4796.043,870.7" "0.15")
(command "_circle" "4797.918,872.7" "0.075")
(command "_circle" "4797.543,872.7" "0.075")
(command "_circle" "4797.168,872.7" "0.15")
(command "_circle" "4796.793,872.7" "0.075")
(command "_circle" "4796.418,872.7" "0.075")
(command "_circle" "4796.043,872.7" "0.15")
(command "_circle" "4797.918,874.7" "0.075")
(command "_circle" "4797.543,874.7" "0.15")
(command "_circle" "4797.168,874.7" "0.15")
(command "_circle" "4796.793,874.7" "0.075")
(command "_circle" "4796.418,874.7" "0.075")
(command "_circle" "4796.043,874.7" "0.15")
(command "_circle" "4797.918,876.7" "0.075")
(command "_circle" "4797.543,876.7" "0.075")
(command "_circle" "4797.168,876.7" "0.075")
(command "_circle" "4796.793,876.7" "0.15")
(command "_circle" "4796.418,876.7" "0.075")
(command "_circle" "4796.043,876.7" "0.15")
(command "_circle" "4797.918,878.7" "0.075")
(command "_circle" "4797.543,878.7" "0.15")
(command "_circle" "4797.168,878.7" "0.075")
(command "_circle" "4796.793,878.7" "0.15")
(command "_circle" "4796.418,878.7" "0.075")
(command "_circle" "4796.043,878.7" "0.15")
(command "_circle" "4797.918,880.7" "0.075")
(command "_circle" "4797.543,880.7" "0.075")
(command "_circle" "4797.168,880.7" "0.15")
(command "_circle" "4796.793,880.7" "0.15")
(command "_circle" "4796.418,880.7" "0.075")
(command "_circle" "4796.043,880.7" "0.15")
(command "_circle" "4797.918,882.7" "0.075")
(command "_circle" "4797.543,882.7" "0.15")
(command "_circle" "4797.168,882.7" "0.15")
(command "_circle" "4796.793,882.7" "0.15")
(command "_circle" "4796.418,882.7" "0.075")
(command "_circle" "4796.043,882.7" "0.15")
(command "_circle" "4797.918,884.7" "0.075")
(command "_circle" "4797.543,884.7" "0.075")
(command "_circle" "4797.168,884.7" "0.075")
(command "_circle" "4796.793,884.7" "0.075")
(command "_circle" "4796.418,884.7" "0.15")
(command "_circle" "4796.043,884.7" "0.15")
(command "_circle" "4797.918,886.7" "0.075")
(command "_circle" "4797.543,886.7" "0.15")
(command "_circle" "4797.168,886.7" "0.075")
(command "_circle" "4796.793,886.7" "0.075")
(command "_circle" "4796.418,886.7" "0.15")
(command "_circle" "4796.043,886.7" "0.15")
(command "_circle" "4797.918,888.7" "0.075")
(command "_circle" "4797.543,888.7" "0.075")
(command "_circle" "4797.168,888.7" "0.15")
(command "_circle" "4796.793,888.7" "0.075")
(command "_circle" "4796.418,888.7" "0.15")
(command "_circle" "4796.043,888.7" "0.15")
(command "_circle" "4797.918,890.7" "0.075")
(command "_circle" "4797.543,890.7" "0.15")
(command "_circle" "4797.168,890.7" "0.15")
(command "_circle" "4796.793,890.7" "0.075")
(command "_circle" "4796.418,890.7" "0.15")
(command "_circle" "4796.043,890.7" "0.15")
(command "_circle" "4797.918,892.7" "0.075")
(command "_circle" "4797.543,892.7" "0.075")
(command "_circle" "4797.168,892.7" "0.075")
(command "_circle" "4796.793,892.7" "0.15")
(command "_circle" "4796.418,892.7" "0.15")
(command "_circle" "4796.043,892.7" "0.15")
(command "_circle" "4797.918,894.7" "0.075")
(command "_circle" "4797.543,894.7" "0.15")
(command "_circle" "4797.168,894.7" "0.075")
(command "_circle" "4796.793,894.7" "0.15")
(command "_circle" "4796.418,894.7" "0.15")
(command "_circle" "4796.043,894.7" "0.15")
(command "_circle" "4797.918,896.7" "0.075")
(command "_circle" "4797.543,896.7" "0.075")
(command "_circle" "4797.168,896.7" "0.15")
(command "_circle" "4796.793,896.7" "0.15")
(command "_circle" "4796.418,896.7" "0.15")
(command "_circle" "4796.043,896.7" "0.15")
(command "_circle" "4797.918,898.7" "0.075")
(command "_circle" "4797.543,898.7" "0.15")
(command "_circle" "4797.168,898.7" "0.15")
(command "_circle" "4796.793,898.7" "0.15")
(command "_circle" "4796.418,898.7" "0.15")
(command "_circle" "4796.043,898.7" "0.15")
(command "_circle" "4797.918,900.7" "0.075")
(command "_circle" "4797.543,900.7" "0.075")
(command "_circle" "4797.168,900.7" "0.075")
(command "_circle" "4796.793,900.7" "0.075")
(command "_circle" "4796.418,900.7" "0.075")
(command "_circle" "4796.043,900.7" "0.075")
(command "_circle" "4795.668,900.7" "0.15")
(command "_circle" "4797.918,902.7" "0.075")
(command "_circle" "4797.543,902.7" "0.15")
(command "_circle" "4797.168,902.7" "0.075")
(command "_circle" "4796.793,902.7" "0.075")
(command "_circle" "4796.418,902.7" "0.075")
(command "_circle" "4796.043,902.7" "0.075")
(command "_circle" "4795.668,902.7" "0.15")
(command "_circle" "4797.918,904.7" "0.075")
(command "_circle" "4797.543,904.7" "0.075")
(command "_circle" "4797.168,904.7" "0.15")
(command "_circle" "4796.793,904.7" "0.075")
(command "_circle" "4796.418,904.7" "0.075")
(command "_circle" "4796.043,904.7" "0.075")
(command "_circle" "4795.668,904.7" "0.15")
(command "_circle" "4797.918,906.7" "0.075")
(command "_circle" "4797.543,906.7" "0.15")
(command "_circle" "4797.168,906.7" "0.15")
(command "_circle" "4796.793,906.7" "0.075")
(command "_circle" "4796.418,906.7" "0.075")
(command "_circle" "4796.043,906.7" "0.075")
(command "_circle" "4795.668,906.7" "0.15")
(command "_circle" "4797.918,908.7" "0.075")
(command "_circle" "4797.543,908.7" "0.075")
(command "_circle" "4797.168,908.7" "0.075")
(command "_circle" "4796.793,908.7" "0.15")
(command "_circle" "4796.418,908.7" "0.075")
(command "_circle" "4796.043,908.7" "0.075")
(command "_circle" "4795.668,908.7" "0.15")
(command "_circle" "4797.918,910.7" "0.075")
(command "_circle" "4797.543,910.7" "0.15")
(command "_circle" "4797.168,910.7" "0.075")
(command "_circle" "4796.793,910.7" "0.15")
(command "_circle" "4796.418,910.7" "0.075")
(command "_circle" "4796.043,910.7" "0.075")
(command "_circle" "4795.668,910.7" "0.15")
(command "_circle" "4797.918,912.7" "0.075")
(command "_circle" "4797.543,912.7" "0.075")
(command "_circle" "4797.168,912.7" "0.15")
(command "_circle" "4796.793,912.7" "0.15")
(command "_circle" "4796.418,912.7" "0.075")
(command "_circle" "4796.043,912.7" "0.075")
(command "_circle" "4795.668,912.7" "0.15")
(command "_circle" "4797.918,914.7" "0.075")
(command "_circle" "4797.543,914.7" "0.15")
(command "_circle" "4797.168,914.7" "0.15")
(command "_circle" "4796.793,914.7" "0.15")
(command "_circle" "4796.418,914.7" "0.075")
(command "_circle" "4796.043,914.7" "0.075")
(command "_circle" "4795.668,914.7" "0.15")
(command "_circle" "4797.918,916.7" "0.075")
(command "_circle" "4797.543,916.7" "0.075")
(command "_circle" "4797.168,916.7" "0.075")
(command "_circle" "4796.793,916.7" "0.075")
(command "_circle" "4796.418,916.7" "0.15")
(command "_circle" "4796.043,916.7" "0.075")
(command "_circle" "4795.668,916.7" "0.15")
(command "_circle" "4797.918,918.7" "0.075")
(command "_circle" "4797.543,918.7" "0.15")
(command "_circle" "4797.168,918.7" "0.075")
(command "_circle" "4796.793,918.7" "0.075")
(command "_circle" "4796.418,918.7" "0.15")
(command "_circle" "4796.043,918.7" "0.075")
(command "_circle" "4795.668,918.7" "0.15")
(command "_circle" "4797.918,920.7" "0.075")
(command "_circle" "4797.543,920.7" "0.075")
(command "_circle" "4797.168,920.7" "0.15")
(command "_circle" "4796.793,920.7" "0.075")
(command "_circle" "4796.418,920.7" "0.15")
(command "_circle" "4796.043,920.7" "0.075")
(command "_circle" "4795.668,920.7" "0.15")
(command "_circle" "4797.918,922.7" "0.075")
(command "_circle" "4797.543,922.7" "0.15")
(command "_circle" "4797.168,922.7" "0.15")
(command "_circle" "4796.793,922.7" "0.075")
(command "_circle" "4796.418,922.7" "0.15")
(command "_circle" "4796.043,922.7" "0.075")
(command "_circle" "4795.668,922.7" "0.15")
(command "_circle" "4797.918,924.7" "0.075")
(command "_circle" "4797.543,924.7" "0.075")
(command "_circle" "4797.168,924.7" "0.075")
(command "_circle" "4796.793,924.7" "0.15")
(command "_circle" "4796.418,924.7" "0.15")
(command "_circle" "4796.043,924.7" "0.075")
(command "_circle" "4795.668,924.7" "0.15")
(command "_circle" "4797.918,926.7" "0.075")
(command "_circle" "4797.543,926.7" "0.15")
(command "_circle" "4797.168,926.7" "0.075")
(command "_circle" "4796.793,926.7" "0.15")
(command "_circle" "4796.418,926.7" "0.15")
(command "_circle" "4796.043,926.7" "0.075")
(command "_circle" "4795.668,926.7" "0.15")
(command "_circle" "4797.918,928.7" "0.075")
(command "_circle" "4797.543,928.7" "0.075")
(command "_circle" "4797.168,928.7" "0.15")
(command "_circle" "4796.793,928.7" "0.15")
(command "_circle" "4796.418,928.7" "0.15")
(command "_circle" "4796.043,928.7" "0.075")
(command "_circle" "4795.668,928.7" "0.15")
(command "_circle" "4797.918,930.7" "0.075")
(command "_circle" "4797.543,930.7" "0.15")
(command "_circle" "4797.168,930.7" "0.15")
(command "_circle" "4796.793,930.7" "0.15")
(command "_circle" "4796.418,930.7" "0.15")
(command "_circle" "4796.043,930.7" "0.075")
(command "_circle" "4795.668,930.7" "0.15")
(command "_circle" "4797.918,932.7" "0.075")
(command "_circle" "4797.543,932.7" "0.075")
(command "_circle" "4797.168,932.7" "0.075")
(command "_circle" "4796.793,932.7" "0.075")
(command "_circle" "4796.418,932.7" "0.075")
(command "_circle" "4796.043,932.7" "0.15")
(command "_circle" "4795.668,932.7" "0.15")
(command "_circle" "4797.918,934.7" "0.075")
(command "_circle" "4797.543,934.7" "0.15")
(command "_circle" "4797.168,934.7" "0.075")
(command "_circle" "4796.793,934.7" "0.075")
(command "_circle" "4796.418,934.7" "0.075")
(command "_circle" "4796.043,934.7" "0.15")
(command "_circle" "4795.668,934.7" "0.15")
(command "_circle" "4797.918,936.7" "0.075")
(command "_circle" "4797.543,936.7" "0.075")
(command "_circle" "4797.168,936.7" "0.15")
(command "_circle" "4796.793,936.7" "0.075")
(command "_circle" "4796.418,936.7" "0.075")
(command "_circle" "4796.043,936.7" "0.15")
(command "_circle" "4795.668,936.7" "0.15")
(command "_circle" "4797.918,938.7" "0.075")
(command "_circle" "4797.543,938.7" "0.15")
(command "_circle" "4797.168,938.7" "0.15")
(command "_circle" "4796.793,938.7" "0.075")
(command "_circle" "4796.418,938.7" "0.075")
(command "_circle" "4796.043,938.7" "0.15")
(command "_circle" "4795.668,938.7" "0.15")
(command "_circle" "4797.918,940.7" "0.075")
(command "_circle" "4797.543,940.7" "0.075")
(command "_circle" "4797.168,940.7" "0.075")
(command "_circle" "4796.793,940.7" "0.15")
(command "_circle" "4796.418,940.7" "0.075")
(command "_circle" "4796.043,940.7" "0.15")
(command "_circle" "4795.668,940.7" "0.15")
(command "_circle" "4797.918,942.7" "0.075")
(command "_circle" "4797.543,942.7" "0.15")
(command "_circle" "4797.168,942.7" "0.075")
(command "_circle" "4796.793,942.7" "0.15")
(command "_circle" "4796.418,942.7" "0.075")
(command "_circle" "4796.043,942.7" "0.15")
(command "_circle" "4795.668,942.7" "0.15")
(command "_circle" "4797.918,944.7" "0.075")
(command "_circle" "4797.543,944.7" "0.075")
(command "_circle" "4797.168,944.7" "0.15")
(command "_circle" "4796.793,944.7" "0.15")
(command "_circle" "4796.418,944.7" "0.075")
(command "_circle" "4796.043,944.7" "0.15")
(command "_circle" "4795.668,944.7" "0.15")
(command "_circle" "4797.918,946.7" "0.075")
(command "_circle" "4797.543,946.7" "0.15")
(command "_circle" "4797.168,946.7" "0.15")
(command "_circle" "4796.793,946.7" "0.15")
(command "_circle" "4796.418,946.7" "0.075")
(command "_circle" "4796.043,946.7" "0.15")
(command "_circle" "4795.668,946.7" "0.15")
(command "_circle" "4797.918,948.7" "0.075")
(command "_circle" "4797.543,948.7" "0.075")
(command "_circle" "4797.168,948.7" "0.075")
(command "_circle" "4796.793,948.7" "0.075")
(command "_circle" "4796.418,948.7" "0.15")
(command "_circle" "4796.043,948.7" "0.15")
(command "_circle" "4795.668,948.7" "0.15")
(command "_circle" "4797.918,950.7" "0.075")
(command "_circle" "4797.543,950.7" "0.15")
(command "_circle" "4797.168,950.7" "0.075")
(command "_circle" "4796.793,950.7" "0.075")
(command "_circle" "4796.418,950.7" "0.15")
(command "_circle" "4796.043,950.7" "0.15")
(command "_circle" "4795.668,950.7" "0.15")
(command "_circle" "4797.918,952.7" "0.075")
(command "_circle" "4797.543,952.7" "0.075")
(command "_circle" "4797.168,952.7" "0.15")
(command "_circle" "4796.793,952.7" "0.075")
(command "_circle" "4796.418,952.7" "0.15")
(command "_circle" "4796.043,952.7" "0.15")
(command "_circle" "4795.668,952.7" "0.15")
(command "_circle" "4797.918,954.7" "0.075")
(command "_circle" "4797.543,954.7" "0.15")
(command "_circle" "4797.168,954.7" "0.15")
(command "_circle" "4796.793,954.7" "0.075")
(command "_circle" "4796.418,954.7" "0.15")
(command "_circle" "4796.043,954.7" "0.15")
(command "_circle" "4795.668,954.7" "0.15")
(command "_circle" "4797.918,956.7" "0.075")
(command "_circle" "4797.543,956.7" "0.075")
(command "_circle" "4797.168,956.7" "0.075")
(command "_circle" "4796.793,956.7" "0.15")
(command "_circle" "4796.418,956.7" "0.15")
(command "_circle" "4796.043,956.7" "0.15")
(command "_circle" "4795.668,956.7" "0.15")
(command "_circle" "4797.918,958.7" "0.075")
(command "_circle" "4797.543,958.7" "0.15")
(command "_circle" "4797.168,958.7" "0.075")
(command "_circle" "4796.793,958.7" "0.15")
(command "_circle" "4796.418,958.7" "0.15")
(command "_circle" "4796.043,958.7" "0.15")
(command "_circle" "4795.668,958.7" "0.15")
(command "_circle" "4797.918,960.7" "0.075")
(command "_circle" "4797.543,960.7" "0.075")
(command "_circle" "4797.168,960.7" "0.15")
(command "_circle" "4796.793,960.7" "0.15")
(command "_circle" "4796.418,960.7" "0.15")
(command "_circle" "4796.043,960.7" "0.15")
(command "_circle" "4795.668,960.7" "0.15")
(command "_circle" "4797.918,962.7" "0.075")
(command "_circle" "4797.543,962.7" "0.15")
(command "_circle" "4797.168,962.7" "0.15")
(command "_circle" "4796.793,962.7" "0.15")
(command "_circle" "4796.418,962.7" "0.15")
(command "_circle" "4796.043,962.7" "0.15")
(command "_circle" "4795.668,962.7" "0.15")
(command "_layer" "set" "nitride" "")
(command "_layer" "set" "text" "")
(command-s "_text" "4786.868,963.3" "2" "-90" "a = 370 nm" )
(sssetfirst nil (ssget "_L"))
(if (not (numberp (vl-string-search "Mac" (getvar "platform")))) (c:txtexp))
(command "_layer" "set" "nitride" "")
(command "_layer" "set" "text" "")
(command-s "_text" "4783.868,963.3" "2" "-90" "gap = 250 nm" )
(sssetfirst nil (ssget "_L"))
(if (not (numberp (vl-string-search "Mac" (getvar "platform")))) (c:txtexp))
(command "_layer" "set" "nitride" "")
(command "_layer" "set" "text" "")
(command-s "_text" "4780.868,963.3" "2" "-90" "amplitude = 137 nm" )
(sssetfirst nil (ssget "_L"))
(if (not (numberp (vl-string-search "Mac" (getvar "platform")))) (c:txtexp))
(command "_layer" "set" "nitride" "")
(command "_layer" "set" "text" "")
(command-s "_text" "4777.868,963.3" "2" "-90" "start width = 280 nm" )
(sssetfirst nil (ssget "_L"))
(if (not (numberp (vl-string-search "Mac" (getvar "platform")))) (c:txtexp))
(command "_layer" "set" "nitride" "")
(command "_layer" "set" "text" "")
(command-s "_text" "4774.868,963.3" "2" "-90" "width = 304 nm" )
(sssetfirst nil (ssget "_L"))
(if (not (numberp (vl-string-search "Mac" (getvar "platform")))) (c:txtexp))
(command "_layer" "set" "nitride" "")
(command "_layer" "set" "text" "")
(command-s "_text" "4771.868,963.3" "2" "-90" "taper: 15" )
(sssetfirst nil (ssget "_L"))
(if (not (numberp (vl-string-search "Mac" (getvar "platform")))) (c:txtexp))
(command "_layer" "set" "nitride" "")
(command "_layer" "set" "text" "")
(command-s "_text" "4768.868,963.3" "2" "-90" "nominal: 150" )
(sssetfirst nil (ssget "_L"))
(if (not (numberp (vl-string-search "Mac" (getvar "platform")))) (c:txtexp))
(command "_layer" "set" "nitride" "")
(command "_layer" "set" "indicators" "")
(setq coords (list 
(list 4720.415 940) 
(list 4720.415 920) 
(list 4700.415 900) 
(list 4720.415 880) 
(list 4720.415 860) 
(list 4720.415 900) 
(list 4720.415 887.0711) 
(list 4707.4861 900) 
(list 4720.415 912.9289) 
(list 4720.415 900)))
(apply 'command (append '("pline") coords '("c")))
(command "._fillet" "radius" "1" "._fillet" "P" (entlast))
(setq coords (list 
(list 4879.585 940) 
(list 4879.585 920) 
(list 4899.585 900) 
(list 4879.585 880) 
(list 4879.585 860) 
(list 4879.585 900) 
(list 4879.585 887.0711) 
(list 4892.5139 900) 
(list 4879.585 912.9289) 
(list 4879.585 900)))
(apply 'command (append '("pline") coords '("c")))
(command "._fillet" "radius" "1" "._fillet" "P" (entlast))
(command "_layer" "set" "holes" "")
(command "_circle" "4718.0629,914.1124" "0.5")
(command "_circle" "4715.7109,911.7603" "0.5")
(command "_circle" "4713.3588,909.4083" "0.5")
(command "_circle" "4711.0067,907.0562" "0.5")
(command "_circle" "4708.6547,904.7041" "0.5")
(command "_circle" "4706.3026,902.3521" "0.5")
(command "_circle" "4703.9505,900" "0.5")
(command "_circle" "4706.3026,897.6479" "0.5")
(command "_circle" "4708.6547,895.2959" "0.5")
(command "_circle" "4711.0067,892.9438" "0.5")
(command "_circle" "4713.3588,890.5917" "0.5")
(command "_circle" "4715.7109,888.2397" "0.5")
(command "_circle" "4718.0629,885.8876" "0.5")
(command "_circle" "4881.9371,914.1124" "0.5")
(command "_circle" "4884.2891,911.7603" "0.5")
(command "_circle" "4886.6412,909.4083" "0.5")
(command "_circle" "4888.9933,907.0562" "0.5")
(command "_circle" "4891.3453,904.7041" "0.5")
(command "_circle" "4893.6974,902.3521" "0.5")
(command "_circle" "4896.0495,900" "0.5")
(command "_circle" "4893.6974,897.6479" "0.5")
(command "_circle" "4891.3453,895.2959" "0.5")
(command "_circle" "4888.9933,892.9438" "0.5")
(command "_circle" "4886.6412,890.5917" "0.5")
(command "_circle" "4884.2891,888.2397" "0.5")
(command "_circle" "4881.9371,885.8876" "0.5")
(command "_layer" "set" "nitride" "")
(command "_block" "blkcoupler15" "4800,900" coupler15 "")
(command "_insert" "blkcoupler15" "4800,900" "1" "1" "0")
(command "_insert" "blkcoupler15" "4800,900" "1" "1" "180")
(command "_block" "blksinglenanobeam15" "4800,900" singlenanobeam15 "")
(command "_insert" "blksinglenanobeam15" "4800,900" "1" "1" "0")
(command "_insert" "blksinglenanobeam15" "4800,900" "1" "1" "180")
(command "_block" "blkanglednodearray15" "4800,900" anglednodearray15 "")
(command "_insert" "blkanglednodearray15" "4800,900" "1" "1" "0")
(command "_insert" "blkanglednodearray15" "4800,900" "1" "1" "180")
(command "_block" "blkcooledsinglenanobeam15" "4800,900" cooledsinglenanobeam15 "")
(command "_insert" "blkcooledsinglenanobeam15" "4800,900" "1" "1" "0")
(command "_insert" "blkcooledsinglenanobeam15" "4800,900" "1" "1" "180")
(command "_block" "blkyjunction15" "4800,900" yjunction15 "")
(command "_insert" "blkyjunction15" "4800,900" "1" "1" "0")
(command "_insert" "blkyjunction15" "4800,900" "1" "1" "180")
; DRAWING BULGING VEE GROOVE
(command "_layer" "set" "vgroove" "")
(setq coords (list 
(list 4725.415 -605) 
(list 4725.415 0) 
(list 4725.415 0) 
(list 4725.415 1800) 
(list 4725.415 1800) 
(list 4725.415 2405) 
(list 4874.585 2405) 
(list 4874.585 1800) 
(list 4874.585 1800) 
(list 4874.585 0) 
(list 4874.585 0) 
(list 4874.585 -605)))
(apply 'command (append '("pline") coords '("c")))
(command "._fillet" "radius" "0" "._fillet" "P" (entlast))
(command "_layer" "set" "window" "")
(command "_rectangle" "4725.415,-1935" "4874.585,-600")
(command "_rectangle" "4725.415,2400" "4874.585,5300")
(command "_layer" "set" "grid" "")
(command "_rectangle" "4726.415,-1934" "4749.9433,-1909.2133")
(command "_array" "last" "" "R" "75" "3" "25.7867" "24.5283")
(command "_rectangle" "4801,-1934" "4824.5283,-1909.2133")
(command "_array" "last" "" "R" "75" "3" "25.7867" "24.5283")
(command "_rectangle" "4726.415,1" "4749.9433,25.7")
(command "_array" "last" "" "R" "70" "3" "25.7" "24.5283")
(command "_rectangle" "4801,1" "4824.5283,25.7")
(command "_array" "last" "" "R" "70" "3" "25.7" "24.5283")
(command "_rectangle" "4726.415,1801" "4749.9433,1825.9185")
(command "_array" "last" "" "R" "135" "3" "25.9185" "24.5283")
(command "_rectangle" "4801,1801" "4824.5283,1825.9185")
(command "_array" "last" "" "R" "135" "3" "25.9185" "24.5283")
(command "_layer" "set" "vgrooveFDA" "")
(command "_rectangle" "4874.585,-2233" "4725.415,-1933")
(command "_layer" "set" "nitride" "")
(command "_layer" "set" "holes" "")
(command "_circle" "4877.085,331.5" "0.5")
(command "_array" "last" "" "R" "379" "1" "3" "2.5")
(command "_circle" "4722.915,331.5" "0.5")
(command "_array" "last" "" "R" "379" "1" "3" "-2.5")
(command "_layer" "set" "nitride" "")
(command "_layer" "set" "window" "")
(command "_layer" "set" "window" "")
(command "_rectangle" "4879.585,0" "5040.415,1800")
(command "._fillet" "radius" "20" "._fillet" "P" (entlast))
(command "_layer" "set" "grid" "")
(command "_rectangle" "4880.585,1" "4902.4179,25.7")
(command "_array" "last" "" "R" "70" "7" "25.7" "22.8329")
(command "_layer" "set" "nitride" "")
; DRAWING REGION LAYER
(command "_layer" "set" "regionLayer15" "")
(command "_rectangle" "4720,-460" "4880,2260")
(command "_layer" "set" "nitride" "")
(setq coupler15 nil)
(setq singlenanobeam15 nil)
(setq anglednodearray15 nil)
(setq cooledsinglenanobeam15 nil)
(setq yjunction15 nil)
; DEVICE #16
(command "_layer" "set" "window" "")
(command "_circle" "5032.915,-415" "5")
(command "_circle" "5032.915,-402.5" "5")
(command "_circle" "5032.915,-390" "5")
(command "_circle" "5032.915,-377.5" "5")
(command "_circle" "5020.415,-415" "5")
(command "_circle" "5020.415,-402.5" "5")
(command "_circle" "5020.415,-390" "5")
(command "_circle" "5020.415,-377.5" "5")
(command "_circle" "5007.915,-415" "5")
(command "_circle" "5007.915,-402.5" "5")
(command "_circle" "5007.915,-390" "5")
(command "_circle" "5007.915,-377.5" "5")
(command "_circle" "4995.415,-415" "5")
(command "_circle" "4995.415,-402.5" "5")
(command "_circle" "4995.415,-390" "5")
(command "_circle" "4995.415,-377.5" "5")
(command "_layer" "set" "nitride" "")
(setq currobj nil)
(setq currobj (ssadd))
; DRAWING COUPLER
(setq coords (list 
(list 5120.0695 -415) 
(list 5120.0695 -413) 
(list 5193.585 -413) 
(list 5193.585 -413) 
(list 5193.9677 -413.0761) 
(list 5194.2921 -413.2929) 
(list 5194.5089 -413.6173) 
(list 5194.585 -414) 
(list 5194.585 -411.8) 
(list 5194.585 -411.8) 
(list 5194.5089 -412.1827) 
(list 5194.2921 -412.5071) 
(list 5193.9677 -412.7239) 
(list 5193.585 -412.8) 
(list 5120.0695 -412.8) 
(list 5120.0695 -410.8) 
(list 5119.9305 -410.8) 
(list 5119.9305 -412.8) 
(list 5046.415 -412.8) 
(list 5046.0323 -412.7239) 
(list 5045.7079 -412.5071) 
(list 5045.4911 -412.1827) 
(list 5045.415 -411.8) 
(list 5045.415 -411.8) 
(list 5045.415 -414) 
(list 5045.4911 -413.6173) 
(list 5045.7079 -413.2929) 
(list 5046.0323 -413.0761) 
(list 5046.415 -413) 
(list 5046.415 -413) 
(list 5119.9305 -413) 
(list 5119.9305 -415)))
(apply 'command (append '("pline") coords '("c")))
(setq currobj (ssadd (entlast) currobj))
(command "._fillet" "radius" "0.3" "._fillet" "P" (entlast))
(command "_layer" "set" "holes" "")
(command "_circle" "5120,-412.9" "0.113")
(setq currobj (ssadd (entlast) currobj))
(command "_layer" "set" "nitride" "")
(command "_layer" "set" "text" "")
(command "_circle" "5119.2,-415" "0.075")
(command "_circle" "5119.2,-414.7" "0.075")
(command "_circle" "5119.2,-414.4" "0.075")
(command "_circle" "5118.9,-415" "0.075")
(command "_circle" "5118.9,-414.7" "0.075")
(command "_circle" "5118.9,-414.4" "0.075")
(command "_circle" "5118.6,-415" "0.075")
(command "_circle" "5118.6,-414.7" "0.075")
(command "_circle" "5118.6,-414.4" "0.075")
(command "_layer" "set" "nitride" "")
(command "_layer" "set" "prebias" "")
(command "_rectangle" "5045.415,-414" "5194.585,-411.8")
(setq currobj (ssadd (entlast) currobj))
(command "_rectangle" "5119.9305,-415" "5120.0695,-410.8")
(setq currobj (ssadd (entlast) currobj))
(command "_layer" "set" "nitride" "")
(setq coupler16 currobj)
(setq currobj nil)
(setq currobj (ssadd))
; DRAWING SINGLE NANOBEAM
(setq coords (list 
(list 5120.0695 -410.8) 
(list 5120.0695 -409.1417) 
(list 5120.0695 -407.4833) 
(list 5120.0695 -405.825) 
(list 5120.0695 -404.1667) 
(list 5120.0695 -402.5083) 
(list 5120.0695 -400.85) 
(list 5120.0695 -399.1917) 
(list 5120.0695 -397.5333) 
(list 5120.0695 -395.875) 
(list 5120.0696 -394.2167) 
(list 5120.0696 -392.5583) 
(list 5120.0696 -390.9) 
(list 5120.0696 -389.2417) 
(list 5120.0697 -387.5833) 
(list 5120.0697 -385.925) 
(list 5120.0698 -384.2667) 
(list 5120.0698 -382.6083) 
(list 5120.0699 -380.95) 
(list 5120.07 -379.2917) 
(list 5120.07 -377.6333) 
(list 5120.0701 -375.975) 
(list 5120.0702 -374.3167) 
(list 5120.0703 -372.6583) 
(list 5120.0704 -371) 
(list 5120.0705 -369.3417) 
(list 5120.0707 -367.6833) 
(list 5120.0708 -366.025) 
(list 5120.071 -364.3667) 
(list 5120.0711 -362.7083) 
(list 5120.0713 -361.05) 
(list 5120.0715 -359.3917) 
(list 5120.0717 -357.7333) 
(list 5120.0719 -356.075) 
(list 5120.0721 -354.4167) 
(list 5120.0724 -352.7583) 
(list 5120.0726 -351.1) 
(list 5120.0729 -349.4417) 
(list 5120.0732 -347.7833) 
(list 5120.0735 -346.125) 
(list 5120.0738 -344.4667) 
(list 5120.0741 -342.8083) 
(list 5120.0745 -341.15) 
(list 5120.0748 -339.4917) 
(list 5120.0752 -337.8333) 
(list 5120.0756 -336.175) 
(list 5120.076 -334.5167) 
(list 5120.0764 -332.8583) 
(list 5120.0769 -331.2) 
(list 5120.0774 -329.5417) 
(list 5120.0779 -327.8833) 
(list 5120.0784 -326.225) 
(list 5120.0789 -324.5667) 
(list 5120.0795 -322.9083) 
(list 5120.08 -321.25) 
(list 5120.0806 -319.5917) 
(list 5120.0812 -317.9333) 
(list 5120.0819 -316.275) 
(list 5120.0825 -314.6167) 
(list 5120.0832 -312.9583) 
(list 5120.0839 -311.3) 
(list 5120.0847 -309.6417) 
(list 5120.0854 -307.9833) 
(list 5120.0862 -306.325) 
(list 5120.087 -304.6667) 
(list 5120.0879 -303.0083) 
(list 5120.0887 -301.35) 
(list 5120.0896 -299.6917) 
(list 5120.0905 -298.0333) 
(list 5120.0915 -296.375) 
(list 5120.0924 -294.7167) 
(list 5120.0934 -293.0583) 
(list 5120.0944 -291.4) 
(list 5120.0955 -289.7417) 
(list 5120.0966 -288.0833) 
(list 5120.0977 -286.425) 
(list 5120.0988 -284.7667) 
(list 5120.1 -283.1083) 
(list 5120.1012 -281.45) 
(list 5120.1025 -279.7917) 
(list 5120.1037 -278.1333) 
(list 5120.105 -276.475) 
(list 5120.1064 -274.8167) 
(list 5120.1077 -273.1583) 
(list 5120.1091 -271.5) 
(list 5120.1105 -269.8417) 
(list 5120.112 -268.1833) 
(list 5120.1135 -266.525) 
(list 5120.1151 -264.8667) 
(list 5120.1166 -263.2083) 
(list 5120.1182 -261.55) 
(list 5120.1199 -259.8917) 
(list 5120.1215 -258.2333) 
(list 5120.1233 -256.575) 
(list 5120.125 -254.9167) 
(list 5120.1268 -253.2583) 
(list 5120.1286 -251.6) 
(list 5120.1305 -249.9417) 
(list 5120.1324 -248.2833) 
(list 5120.1344 -246.625) 
(list 5120.1363 -244.9667) 
(list 5120.1384 -243.3083) 
(list 5120.1404 -241.65) 
(list 5120.1425 -239.9917) 
(list 5120.1447 -238.3333) 
(list 5120.1469 -236.675) 
(list 5120.1491 -235.0167) 
(list 5120.1514 -233.3583) 
(list 5120.1537 -231.7) 
(list 5120.1561 -230.0417) 
(list 5120.1585 -228.3833) 
(list 5120.1609 -226.725) 
(list 5120.1634 -225.0667) 
(list 5120.1659 -223.4083) 
(list 5120.1685 -221.75) 
(list 5120.1712 -220.0917) 
(list 5120.1738 -218.4333) 
(list 5120.1766 -216.775) 
(list 5120.1793 -215.1167) 
(list 5120.1821 -213.4583) 
(list 5120.185 -211.8) 
(list 5119.815 -211.8) 
(list 5119.8179 -213.4583) 
(list 5119.8207 -215.1167) 
(list 5119.8234 -216.775) 
(list 5119.8262 -218.4333) 
(list 5119.8288 -220.0917) 
(list 5119.8315 -221.75) 
(list 5119.8341 -223.4083) 
(list 5119.8366 -225.0667) 
(list 5119.8391 -226.725) 
(list 5119.8415 -228.3833) 
(list 5119.8439 -230.0417) 
(list 5119.8463 -231.7) 
(list 5119.8486 -233.3583) 
(list 5119.8509 -235.0167) 
(list 5119.8531 -236.675) 
(list 5119.8553 -238.3333) 
(list 5119.8575 -239.9917) 
(list 5119.8596 -241.65) 
(list 5119.8616 -243.3083) 
(list 5119.8637 -244.9667) 
(list 5119.8656 -246.625) 
(list 5119.8676 -248.2833) 
(list 5119.8695 -249.9417) 
(list 5119.8714 -251.6) 
(list 5119.8732 -253.2583) 
(list 5119.875 -254.9167) 
(list 5119.8767 -256.575) 
(list 5119.8785 -258.2333) 
(list 5119.8801 -259.8917) 
(list 5119.8818 -261.55) 
(list 5119.8834 -263.2083) 
(list 5119.8849 -264.8667) 
(list 5119.8865 -266.525) 
(list 5119.888 -268.1833) 
(list 5119.8895 -269.8417) 
(list 5119.8909 -271.5) 
(list 5119.8923 -273.1583) 
(list 5119.8936 -274.8167) 
(list 5119.895 -276.475) 
(list 5119.8963 -278.1333) 
(list 5119.8975 -279.7917) 
(list 5119.8988 -281.45) 
(list 5119.9 -283.1083) 
(list 5119.9012 -284.7667) 
(list 5119.9023 -286.425) 
(list 5119.9034 -288.0833) 
(list 5119.9045 -289.7417) 
(list 5119.9056 -291.4) 
(list 5119.9066 -293.0583) 
(list 5119.9076 -294.7167) 
(list 5119.9085 -296.375) 
(list 5119.9095 -298.0333) 
(list 5119.9104 -299.6917) 
(list 5119.9113 -301.35) 
(list 5119.9121 -303.0083) 
(list 5119.913 -304.6667) 
(list 5119.9138 -306.325) 
(list 5119.9146 -307.9833) 
(list 5119.9153 -309.6417) 
(list 5119.9161 -311.3) 
(list 5119.9168 -312.9583) 
(list 5119.9175 -314.6167) 
(list 5119.9181 -316.275) 
(list 5119.9188 -317.9333) 
(list 5119.9194 -319.5917) 
(list 5119.92 -321.25) 
(list 5119.9205 -322.9083) 
(list 5119.9211 -324.5667) 
(list 5119.9216 -326.225) 
(list 5119.9221 -327.8833) 
(list 5119.9226 -329.5417) 
(list 5119.9231 -331.2) 
(list 5119.9236 -332.8583) 
(list 5119.924 -334.5167) 
(list 5119.9244 -336.175) 
(list 5119.9248 -337.8333) 
(list 5119.9252 -339.4917) 
(list 5119.9255 -341.15) 
(list 5119.9259 -342.8083) 
(list 5119.9262 -344.4667) 
(list 5119.9265 -346.125) 
(list 5119.9268 -347.7833) 
(list 5119.9271 -349.4417) 
(list 5119.9274 -351.1) 
(list 5119.9276 -352.7583) 
(list 5119.9279 -354.4167) 
(list 5119.9281 -356.075) 
(list 5119.9283 -357.7333) 
(list 5119.9285 -359.3917) 
(list 5119.9287 -361.05) 
(list 5119.9289 -362.7083) 
(list 5119.929 -364.3667) 
(list 5119.9292 -366.025) 
(list 5119.9293 -367.6833) 
(list 5119.9295 -369.3417) 
(list 5119.9296 -371) 
(list 5119.9297 -372.6583) 
(list 5119.9298 -374.3167) 
(list 5119.9299 -375.975) 
(list 5119.93 -377.6333) 
(list 5119.93 -379.2917) 
(list 5119.9301 -380.95) 
(list 5119.9302 -382.6083) 
(list 5119.9302 -384.2667) 
(list 5119.9303 -385.925) 
(list 5119.9303 -387.5833) 
(list 5119.9304 -389.2417) 
(list 5119.9304 -390.9) 
(list 5119.9304 -392.5583) 
(list 5119.9304 -394.2167) 
(list 5119.9305 -395.875) 
(list 5119.9305 -397.5333) 
(list 5119.9305 -399.1917) 
(list 5119.9305 -400.85) 
(list 5119.9305 -402.5083) 
(list 5119.9305 -404.1667) 
(list 5119.9305 -405.825) 
(list 5119.9305 -407.4833) 
(list 5119.9305 -409.1417) 
(list 5119.9305 -410.8)))
(apply 'command (append '("pline") coords '("c")))
(setq currobj (ssadd (entlast) currobj))
(command "_layer" "set" "prebias" "")
(command "_rectangle" "5119.815,-410.8" "5120.185,-211.8")
(setq currobj (ssadd (entlast) currobj))
(command "_layer" "set" "nitride" "")
(setq singlenanobeam16 currobj)
(setq currobj nil)
(setq currobj (ssadd))
; DRAWING NODE ARRAY
(setq coords (list 
(list 5120.185 -211.8) 
(list 5120.5625 -201.8) 
(list 5120.5625 -201.8) 
(list 5120.5625 -200.8) 
(list 5194.585 -212.6864) 
(list 5194.585 -207.7434) 
(list 5120.5625 -197.357) 
(list 5120.5625 -196.357) 
(list 5120.5625 -196.357) 
(list 5120.2625 -186.357) 
(list 5119.7375 -186.357) 
(list 5119.4375 -196.357) 
(list 5119.4375 -196.357) 
(list 5119.4375 -197.357) 
(list 5045.415 -207.7434) 
(list 5045.415 -212.6864) 
(list 5119.4375 -200.8) 
(list 5119.4375 -201.8) 
(list 5119.4375 -201.8) 
(list 5119.815 -211.8)))
(apply 'command (append '("pline") coords '("c")))
(setq currobj (ssadd (entlast) currobj))
(command "_layer" "set" "prebias" "")
(setq coords (list 
(list 5119.4375 -212.6864) 
(list 5119.4375 -200.8) 
(list 5045.415 -212.6864) 
(list 5045.415 -207.7434) 
(list 5119.4375 -197.357) 
(list 5119.4375 -186.357) 
(list 5120.5625 -186.357) 
(list 5120.5625 -197.357) 
(list 5194.585 -207.7434) 
(list 5194.585 -212.6864) 
(list 5120.5625 -200.8) 
(list 5120.5625 -212.6864)))
(apply 'command (append '("pline") coords '("c")))
(setq currobj (ssadd (entlast) currobj))
(command "_layer" "set" "nitride" "")
(command "_layer" "set" "fda1" "")
(setq coords (list 
(list 5120.5625 -200.657) 
(list 5194.585 -212.5434) 
(list 5194.585 -212.3664) 
(list 5120.5625 -200.58)))
(apply 'command (append '("pline") coords '("c")))
(setq currobj (ssadd (entlast) currobj))
(setq coords (list 
(list 5120.5625 -200.437) 
(list 5194.585 -212.2234) 
(list 5194.585 -212.0464) 
(list 5120.5625 -200.36)))
(apply 'command (append '("pline") coords '("c")))
(setq currobj (ssadd (entlast) currobj))
(setq coords (list 
(list 5120.5625 -200.217) 
(list 5194.585 -211.9034) 
(list 5194.585 -211.7264) 
(list 5120.5625 -200.14)))
(apply 'command (append '("pline") coords '("c")))
(setq currobj (ssadd (entlast) currobj))
(setq coords (list 
(list 5120.5625 -199.997) 
(list 5194.585 -211.5834) 
(list 5194.585 -211.4064) 
(list 5120.5625 -199.92)))
(apply 'command (append '("pline") coords '("c")))
(setq currobj (ssadd (entlast) currobj))
(setq coords (list 
(list 5120.5625 -199.777) 
(list 5194.585 -211.2634) 
(list 5194.585 -211.0864) 
(list 5120.5625 -199.7)))
(apply 'command (append '("pline") coords '("c")))
(setq currobj (ssadd (entlast) currobj))
(setq coords (list 
(list 5120.5625 -199.557) 
(list 5194.585 -210.9434) 
(list 5194.585 -210.7664) 
(list 5120.5625 -199.48)))
(apply 'command (append '("pline") coords '("c")))
(setq currobj (ssadd (entlast) currobj))
(setq coords (list 
(list 5120.5625 -199.337) 
(list 5194.585 -210.6234) 
(list 5194.585 -210.4464) 
(list 5120.5625 -199.26)))
(apply 'command (append '("pline") coords '("c")))
(setq currobj (ssadd (entlast) currobj))
(setq coords (list 
(list 5120.5625 -199.117) 
(list 5194.585 -210.3034) 
(list 5194.585 -210.1264) 
(list 5120.5625 -199.04)))
(apply 'command (append '("pline") coords '("c")))
(setq currobj (ssadd (entlast) currobj))
(setq coords (list 
(list 5120.5625 -198.897) 
(list 5194.585 -209.9834) 
(list 5194.585 -209.8064) 
(list 5120.5625 -198.82)))
(apply 'command (append '("pline") coords '("c")))
(setq currobj (ssadd (entlast) currobj))
(setq coords (list 
(list 5120.5625 -198.677) 
(list 5194.585 -209.6634) 
(list 5194.585 -209.4864) 
(list 5120.5625 -198.6)))
(apply 'command (append '("pline") coords '("c")))
(setq currobj (ssadd (entlast) currobj))
(setq coords (list 
(list 5120.5625 -198.457) 
(list 5194.585 -209.3434) 
(list 5194.585 -209.1664) 
(list 5120.5625 -198.38)))
(apply 'command (append '("pline") coords '("c")))
(setq currobj (ssadd (entlast) currobj))
(setq coords (list 
(list 5120.5625 -198.237) 
(list 5194.585 -209.0234) 
(list 5194.585 -208.8464) 
(list 5120.5625 -198.16)))
(apply 'command (append '("pline") coords '("c")))
(setq currobj (ssadd (entlast) currobj))
(setq coords (list 
(list 5120.5625 -198.017) 
(list 5194.585 -208.7034) 
(list 5194.585 -208.5264) 
(list 5120.5625 -197.94)))
(apply 'command (append '("pline") coords '("c")))
(setq currobj (ssadd (entlast) currobj))
(setq coords (list 
(list 5120.5625 -197.797) 
(list 5194.585 -208.3834) 
(list 5194.585 -208.2064) 
(list 5120.5625 -197.72)))
(apply 'command (append '("pline") coords '("c")))
(setq currobj (ssadd (entlast) currobj))
(setq coords (list 
(list 5120.5625 -197.577) 
(list 5194.585 -208.0634) 
(list 5194.585 -207.8864) 
(list 5120.5625 -197.5)))
(apply 'command (append '("pline") coords '("c")))
(setq currobj (ssadd (entlast) currobj))
(setq coords (list 
(list 5119.4375 -197.5) 
(list 5045.415 -207.8864) 
(list 5045.415 -208.0634) 
(list 5119.4375 -197.577)))
(apply 'command (append '("pline") coords '("c")))
(setq currobj (ssadd (entlast) currobj))
(setq coords (list 
(list 5119.4375 -197.72) 
(list 5045.415 -208.2064) 
(list 5045.415 -208.3834) 
(list 5119.4375 -197.797)))
(apply 'command (append '("pline") coords '("c")))
(setq currobj (ssadd (entlast) currobj))
(setq coords (list 
(list 5119.4375 -197.94) 
(list 5045.415 -208.5264) 
(list 5045.415 -208.7034) 
(list 5119.4375 -198.017)))
(apply 'command (append '("pline") coords '("c")))
(setq currobj (ssadd (entlast) currobj))
(setq coords (list 
(list 5119.4375 -198.16) 
(list 5045.415 -208.8464) 
(list 5045.415 -209.0234) 
(list 5119.4375 -198.237)))
(apply 'command (append '("pline") coords '("c")))
(setq currobj (ssadd (entlast) currobj))
(setq coords (list 
(list 5119.4375 -198.38) 
(list 5045.415 -209.1664) 
(list 5045.415 -209.3434) 
(list 5119.4375 -198.457)))
(apply 'command (append '("pline") coords '("c")))
(setq currobj (ssadd (entlast) currobj))
(setq coords (list 
(list 5119.4375 -198.6) 
(list 5045.415 -209.4864) 
(list 5045.415 -209.6634) 
(list 5119.4375 -198.677)))
(apply 'command (append '("pline") coords '("c")))
(setq currobj (ssadd (entlast) currobj))
(setq coords (list 
(list 5119.4375 -198.82) 
(list 5045.415 -209.8064) 
(list 5045.415 -209.9834) 
(list 5119.4375 -198.897)))
(apply 'command (append '("pline") coords '("c")))
(setq currobj (ssadd (entlast) currobj))
(setq coords (list 
(list 5119.4375 -199.04) 
(list 5045.415 -210.1264) 
(list 5045.415 -210.3034) 
(list 5119.4375 -199.117)))
(apply 'command (append '("pline") coords '("c")))
(setq currobj (ssadd (entlast) currobj))
(setq coords (list 
(list 5119.4375 -199.26) 
(list 5045.415 -210.4464) 
(list 5045.415 -210.6234) 
(list 5119.4375 -199.337)))
(apply 'command (append '("pline") coords '("c")))
(setq currobj (ssadd (entlast) currobj))
(setq coords (list 
(list 5119.4375 -199.48) 
(list 5045.415 -210.7664) 
(list 5045.415 -210.9434) 
(list 5119.4375 -199.557)))
(apply 'command (append '("pline") coords '("c")))
(setq currobj (ssadd (entlast) currobj))
(setq coords (list 
(list 5119.4375 -199.7) 
(list 5045.415 -211.0864) 
(list 5045.415 -211.2634) 
(list 5119.4375 -199.777)))
(apply 'command (append '("pline") coords '("c")))
(setq currobj (ssadd (entlast) currobj))
(setq coords (list 
(list 5119.4375 -199.92) 
(list 5045.415 -211.4064) 
(list 5045.415 -211.5834) 
(list 5119.4375 -199.997)))
(apply 'command (append '("pline") coords '("c")))
(setq currobj (ssadd (entlast) currobj))
(setq coords (list 
(list 5119.4375 -200.14) 
(list 5045.415 -211.7264) 
(list 5045.415 -211.9034) 
(list 5119.4375 -200.217)))
(apply 'command (append '("pline") coords '("c")))
(setq currobj (ssadd (entlast) currobj))
(setq coords (list 
(list 5119.4375 -200.36) 
(list 5045.415 -212.0464) 
(list 5045.415 -212.2234) 
(list 5119.4375 -200.437)))
(apply 'command (append '("pline") coords '("c")))
(setq currobj (ssadd (entlast) currobj))
(setq coords (list 
(list 5119.4375 -200.58) 
(list 5045.415 -212.3664) 
(list 5045.415 -212.5434) 
(list 5119.4375 -200.657)))
(apply 'command (append '("pline") coords '("c")))
(setq currobj (ssadd (entlast) currobj))
(command "_layer" "set" "nitride" "")
(command "_layer" "set" "text" "")
(command "_circle" "5118.985,-211.8" "0.075")
(command "_circle" "5118.985,-211.5" "0.075")
(command "_circle" "5118.985,-211.2" "0.075")
(command "_circle" "5118.985,-210.9" "0.075")
(command "_circle" "5118.985,-210.6" "0.075")
(command "_circle" "5118.685,-211.8" "0.075")
(command "_circle" "5118.685,-211.5" "0.075")
(command "_circle" "5118.685,-211.2" "0.075")
(command "_circle" "5118.685,-210.9" "0.075")
(command "_circle" "5118.685,-210.6" "0.075")
(command "_circle" "5118.385,-211.8" "0.075")
(command "_circle" "5118.385,-211.5" "0.075")
(command "_circle" "5118.385,-211.2" "0.075")
(command "_circle" "5118.385,-210.9" "0.075")
(command "_circle" "5118.385,-210.6" "0.075")
(command "_circle" "5118.085,-211.8" "0.075")
(command "_circle" "5118.085,-211.5" "0.075")
(command "_circle" "5118.085,-211.2" "0.075")
(command "_circle" "5118.085,-210.9" "0.075")
(command "_circle" "5118.085,-210.6" "0.075")
(command "_circle" "5117.785,-211.8" "0.075")
(command "_circle" "5117.785,-211.5" "0.075")
(command "_circle" "5117.785,-211.2" "0.075")
(command "_circle" "5117.785,-210.9" "0.075")
(command "_circle" "5117.785,-210.6" "0.075")
(command "_layer" "set" "nitride" "")
(setq anglednodearray16 currobj)
(setq currobj nil)
(setq currobj (ssadd))
; DRAWING COOLED SINGLE NANOBEAM
(setq coords (list 
(list 5120.2625 -186.357) 
(list 5120.2625 -181.357) 
(list 5119.7375 -181.357) 
(list 5119.7375 -186.357)))
(apply 'command (append '("pline") coords '("c")))
(setq currobj (ssadd (entlast) currobj))
(command "_layer" "set" "prebias" "")
(command "_rectangle" "5119.7375,-186.357" "5120.2625,-181.357")
(setq currobj (ssadd (entlast) currobj))
(command "_layer" "set" "nitride" "")
(setq coords (list 
(list 5120.2625 -181.357) 
(list 5120.5625 -171.357) 
(list 5120.5625 -171.357) 
(list 5120.5625 -170.357) 
(list 5194.585 -171.107) 
(list 5194.585 -166.164) 
(list 5120.5625 -166.914) 
(list 5120.5625 -165.914) 
(list 5120.5625 -165.914) 
(list 5120.2625 -155.914) 
(list 5119.7375 -155.914) 
(list 5119.4375 -165.914) 
(list 5119.4375 -165.914) 
(list 5119.4375 -166.914) 
(list 5045.415 -166.164) 
(list 5045.415 -171.107) 
(list 5119.4375 -170.357) 
(list 5119.4375 -171.357) 
(list 5119.4375 -171.357) 
(list 5119.7375 -181.357)))
(apply 'command (append '("pline") coords '("c")))
(setq currobj (ssadd (entlast) currobj))
(command "_layer" "set" "prebias" "")
(setq coords (list 
(list 5119.4375 -181.357) 
(list 5119.4375 -170.357) 
(list 5045.415 -171.107) 
(list 5045.415 -166.164) 
(list 5119.4375 -166.914) 
(list 5119.4375 -155.914) 
(list 5120.5625 -155.914) 
(list 5120.5625 -166.914) 
(list 5194.585 -166.164) 
(list 5194.585 -171.107) 
(list 5120.5625 -170.357) 
(list 5120.5625 -181.357)))
(apply 'command (append '("pline") coords '("c")))
(setq currobj (ssadd (entlast) currobj))
(command "_layer" "set" "nitride" "")
(command "_layer" "set" "fda1" "")
(setq coords (list 
(list 5120.5625 -170.214) 
(list 5194.585 -170.964) 
(list 5194.585 -170.787) 
(list 5120.5625 -170.137)))
(apply 'command (append '("pline") coords '("c")))
(setq currobj (ssadd (entlast) currobj))
(setq coords (list 
(list 5120.5625 -169.994) 
(list 5194.585 -170.644) 
(list 5194.585 -170.467) 
(list 5120.5625 -169.917)))
(apply 'command (append '("pline") coords '("c")))
(setq currobj (ssadd (entlast) currobj))
(setq coords (list 
(list 5120.5625 -169.774) 
(list 5194.585 -170.324) 
(list 5194.585 -170.147) 
(list 5120.5625 -169.697)))
(apply 'command (append '("pline") coords '("c")))
(setq currobj (ssadd (entlast) currobj))
(setq coords (list 
(list 5120.5625 -169.554) 
(list 5194.585 -170.004) 
(list 5194.585 -169.827) 
(list 5120.5625 -169.477)))
(apply 'command (append '("pline") coords '("c")))
(setq currobj (ssadd (entlast) currobj))
(setq coords (list 
(list 5120.5625 -169.334) 
(list 5194.585 -169.684) 
(list 5194.585 -169.507) 
(list 5120.5625 -169.257)))
(apply 'command (append '("pline") coords '("c")))
(setq currobj (ssadd (entlast) currobj))
(setq coords (list 
(list 5120.5625 -169.114) 
(list 5194.585 -169.364) 
(list 5194.585 -169.187) 
(list 5120.5625 -169.037)))
(apply 'command (append '("pline") coords '("c")))
(setq currobj (ssadd (entlast) currobj))
(setq coords (list 
(list 5120.5625 -168.894) 
(list 5194.585 -169.044) 
(list 5194.585 -168.867) 
(list 5120.5625 -168.817)))
(apply 'command (append '("pline") coords '("c")))
(setq currobj (ssadd (entlast) currobj))
(setq coords (list 
(list 5120.5625 -168.674) 
(list 5194.585 -168.724) 
(list 5194.585 -168.547) 
(list 5120.5625 -168.597)))
(apply 'command (append '("pline") coords '("c")))
(setq currobj (ssadd (entlast) currobj))
(setq coords (list 
(list 5120.5625 -168.454) 
(list 5194.585 -168.404) 
(list 5194.585 -168.227) 
(list 5120.5625 -168.377)))
(apply 'command (append '("pline") coords '("c")))
(setq currobj (ssadd (entlast) currobj))
(setq coords (list 
(list 5120.5625 -168.234) 
(list 5194.585 -168.084) 
(list 5194.585 -167.907) 
(list 5120.5625 -168.157)))
(apply 'command (append '("pline") coords '("c")))
(setq currobj (ssadd (entlast) currobj))
(setq coords (list 
(list 5120.5625 -168.014) 
(list 5194.585 -167.764) 
(list 5194.585 -167.587) 
(list 5120.5625 -167.937)))
(apply 'command (append '("pline") coords '("c")))
(setq currobj (ssadd (entlast) currobj))
(setq coords (list 
(list 5120.5625 -167.794) 
(list 5194.585 -167.444) 
(list 5194.585 -167.267) 
(list 5120.5625 -167.717)))
(apply 'command (append '("pline") coords '("c")))
(setq currobj (ssadd (entlast) currobj))
(setq coords (list 
(list 5120.5625 -167.574) 
(list 5194.585 -167.124) 
(list 5194.585 -166.947) 
(list 5120.5625 -167.497)))
(apply 'command (append '("pline") coords '("c")))
(setq currobj (ssadd (entlast) currobj))
(setq coords (list 
(list 5120.5625 -167.354) 
(list 5194.585 -166.804) 
(list 5194.585 -166.627) 
(list 5120.5625 -167.277)))
(apply 'command (append '("pline") coords '("c")))
(setq currobj (ssadd (entlast) currobj))
(setq coords (list 
(list 5120.5625 -167.134) 
(list 5194.585 -166.484) 
(list 5194.585 -166.307) 
(list 5120.5625 -167.057)))
(apply 'command (append '("pline") coords '("c")))
(setq currobj (ssadd (entlast) currobj))
(setq coords (list 
(list 5119.4375 -167.057) 
(list 5045.415 -166.307) 
(list 5045.415 -166.484) 
(list 5119.4375 -167.134)))
(apply 'command (append '("pline") coords '("c")))
(setq currobj (ssadd (entlast) currobj))
(setq coords (list 
(list 5119.4375 -167.277) 
(list 5045.415 -166.627) 
(list 5045.415 -166.804) 
(list 5119.4375 -167.354)))
(apply 'command (append '("pline") coords '("c")))
(setq currobj (ssadd (entlast) currobj))
(setq coords (list 
(list 5119.4375 -167.497) 
(list 5045.415 -166.947) 
(list 5045.415 -167.124) 
(list 5119.4375 -167.574)))
(apply 'command (append '("pline") coords '("c")))
(setq currobj (ssadd (entlast) currobj))
(setq coords (list 
(list 5119.4375 -167.717) 
(list 5045.415 -167.267) 
(list 5045.415 -167.444) 
(list 5119.4375 -167.794)))
(apply 'command (append '("pline") coords '("c")))
(setq currobj (ssadd (entlast) currobj))
(setq coords (list 
(list 5119.4375 -167.937) 
(list 5045.415 -167.587) 
(list 5045.415 -167.764) 
(list 5119.4375 -168.014)))
(apply 'command (append '("pline") coords '("c")))
(setq currobj (ssadd (entlast) currobj))
(setq coords (list 
(list 5119.4375 -168.157) 
(list 5045.415 -167.907) 
(list 5045.415 -168.084) 
(list 5119.4375 -168.234)))
(apply 'command (append '("pline") coords '("c")))
(setq currobj (ssadd (entlast) currobj))
(setq coords (list 
(list 5119.4375 -168.377) 
(list 5045.415 -168.227) 
(list 5045.415 -168.404) 
(list 5119.4375 -168.454)))
(apply 'command (append '("pline") coords '("c")))
(setq currobj (ssadd (entlast) currobj))
(setq coords (list 
(list 5119.4375 -168.597) 
(list 5045.415 -168.547) 
(list 5045.415 -168.724) 
(list 5119.4375 -168.674)))
(apply 'command (append '("pline") coords '("c")))
(setq currobj (ssadd (entlast) currobj))
(setq coords (list 
(list 5119.4375 -168.817) 
(list 5045.415 -168.867) 
(list 5045.415 -169.044) 
(list 5119.4375 -168.894)))
(apply 'command (append '("pline") coords '("c")))
(setq currobj (ssadd (entlast) currobj))
(setq coords (list 
(list 5119.4375 -169.037) 
(list 5045.415 -169.187) 
(list 5045.415 -169.364) 
(list 5119.4375 -169.114)))
(apply 'command (append '("pline") coords '("c")))
(setq currobj (ssadd (entlast) currobj))
(setq coords (list 
(list 5119.4375 -169.257) 
(list 5045.415 -169.507) 
(list 5045.415 -169.684) 
(list 5119.4375 -169.334)))
(apply 'command (append '("pline") coords '("c")))
(setq currobj (ssadd (entlast) currobj))
(setq coords (list 
(list 5119.4375 -169.477) 
(list 5045.415 -169.827) 
(list 5045.415 -170.004) 
(list 5119.4375 -169.554)))
(apply 'command (append '("pline") coords '("c")))
(setq currobj (ssadd (entlast) currobj))
(setq coords (list 
(list 5119.4375 -169.697) 
(list 5045.415 -170.147) 
(list 5045.415 -170.324) 
(list 5119.4375 -169.774)))
(apply 'command (append '("pline") coords '("c")))
(setq currobj (ssadd (entlast) currobj))
(setq coords (list 
(list 5119.4375 -169.917) 
(list 5045.415 -170.467) 
(list 5045.415 -170.644) 
(list 5119.4375 -169.994)))
(apply 'command (append '("pline") coords '("c")))
(setq currobj (ssadd (entlast) currobj))
(setq coords (list 
(list 5119.4375 -170.137) 
(list 5045.415 -170.787) 
(list 5045.415 -170.964) 
(list 5119.4375 -170.214)))
(apply 'command (append '("pline") coords '("c")))
(setq currobj (ssadd (entlast) currobj))
(command "_layer" "set" "nitride" "")
(command "_layer" "set" "text" "")
(command "_circle" "5119.0625,-181.357" "0.075")
(command "_circle" "5119.0625,-181.057" "0.075")
(command "_circle" "5119.0625,-180.757" "0.075")
(command "_circle" "5119.0625,-180.457" "0.075")
(command "_circle" "5119.0625,-180.157" "0.075")
(command "_circle" "5118.7625,-181.357" "0.075")
(command "_circle" "5118.7625,-181.057" "0.075")
(command "_circle" "5118.7625,-180.757" "0.075")
(command "_circle" "5118.7625,-180.457" "0.075")
(command "_circle" "5118.7625,-180.157" "0.075")
(command "_circle" "5118.4625,-181.357" "0.075")
(command "_circle" "5118.4625,-181.057" "0.075")
(command "_circle" "5118.4625,-180.757" "0.075")
(command "_circle" "5118.4625,-180.457" "0.075")
(command "_circle" "5118.4625,-180.157" "0.075")
(command "_circle" "5118.1625,-181.357" "0.075")
(command "_circle" "5118.1625,-181.057" "0.075")
(command "_circle" "5118.1625,-180.757" "0.075")
(command "_circle" "5118.1625,-180.457" "0.075")
(command "_circle" "5118.1625,-180.157" "0.075")
(command "_circle" "5117.8625,-181.357" "0.075")
(command "_circle" "5117.8625,-181.057" "0.075")
(command "_circle" "5117.8625,-180.757" "0.075")
(command "_circle" "5117.8625,-180.457" "0.075")
(command "_circle" "5117.8625,-180.157" "0.075")
(command "_layer" "set" "nitride" "")
(setq coords (list 
(list 5120.2625 -155.914) 
(list 5120.2625 -40.2693) 
(list 5119.7375 -40.2693) 
(list 5119.7375 -155.914)))
(apply 'command (append '("pline") coords '("c")))
(setq currobj (ssadd (entlast) currobj))
(command "_layer" "set" "prebias" "")
(command "_rectangle" "5119.7375,-155.914" "5120.2625,-40.2693")
(setq currobj (ssadd (entlast) currobj))
(command "_layer" "set" "nitride" "")
(setq coords (list 
(list 5120.2625 -40.2693) 
(list 5120.5625 -30.2693) 
(list 5120.5625 -30.2693) 
(list 5120.5625 -29.2693) 
(list 5194.585 -30.0193) 
(list 5194.585 -25.0763) 
(list 5120.5625 -25.8263) 
(list 5120.5625 -24.8263) 
(list 5120.5625 -24.8263) 
(list 5120.2625 -14.8263) 
(list 5119.7375 -14.8263) 
(list 5119.4375 -24.8263) 
(list 5119.4375 -24.8263) 
(list 5119.4375 -25.8263) 
(list 5045.415 -25.0763) 
(list 5045.415 -30.0193) 
(list 5119.4375 -29.2693) 
(list 5119.4375 -30.2693) 
(list 5119.4375 -30.2693) 
(list 5119.7375 -40.2693)))
(apply 'command (append '("pline") coords '("c")))
(setq currobj (ssadd (entlast) currobj))
(command "_layer" "set" "prebias" "")
(setq coords (list 
(list 5119.4375 -40.2693) 
(list 5119.4375 -29.2693) 
(list 5045.415 -30.0193) 
(list 5045.415 -25.0763) 
(list 5119.4375 -25.8263) 
(list 5119.4375 -14.8263) 
(list 5120.5625 -14.8263) 
(list 5120.5625 -25.8263) 
(list 5194.585 -25.0763) 
(list 5194.585 -30.0193) 
(list 5120.5625 -29.2693) 
(list 5120.5625 -40.2693)))
(apply 'command (append '("pline") coords '("c")))
(setq currobj (ssadd (entlast) currobj))
(command "_layer" "set" "nitride" "")
(command "_layer" "set" "fda1" "")
(setq coords (list 
(list 5120.5625 -29.1263) 
(list 5194.585 -29.8763) 
(list 5194.585 -29.6993) 
(list 5120.5625 -29.0493)))
(apply 'command (append '("pline") coords '("c")))
(setq currobj (ssadd (entlast) currobj))
(setq coords (list 
(list 5120.5625 -28.9063) 
(list 5194.585 -29.5563) 
(list 5194.585 -29.3793) 
(list 5120.5625 -28.8293)))
(apply 'command (append '("pline") coords '("c")))
(setq currobj (ssadd (entlast) currobj))
(setq coords (list 
(list 5120.5625 -28.6863) 
(list 5194.585 -29.2363) 
(list 5194.585 -29.0593) 
(list 5120.5625 -28.6093)))
(apply 'command (append '("pline") coords '("c")))
(setq currobj (ssadd (entlast) currobj))
(setq coords (list 
(list 5120.5625 -28.4663) 
(list 5194.585 -28.9163) 
(list 5194.585 -28.7393) 
(list 5120.5625 -28.3893)))
(apply 'command (append '("pline") coords '("c")))
(setq currobj (ssadd (entlast) currobj))
(setq coords (list 
(list 5120.5625 -28.2463) 
(list 5194.585 -28.5963) 
(list 5194.585 -28.4193) 
(list 5120.5625 -28.1693)))
(apply 'command (append '("pline") coords '("c")))
(setq currobj (ssadd (entlast) currobj))
(setq coords (list 
(list 5120.5625 -28.0263) 
(list 5194.585 -28.2763) 
(list 5194.585 -28.0993) 
(list 5120.5625 -27.9493)))
(apply 'command (append '("pline") coords '("c")))
(setq currobj (ssadd (entlast) currobj))
(setq coords (list 
(list 5120.5625 -27.8063) 
(list 5194.585 -27.9563) 
(list 5194.585 -27.7793) 
(list 5120.5625 -27.7293)))
(apply 'command (append '("pline") coords '("c")))
(setq currobj (ssadd (entlast) currobj))
(setq coords (list 
(list 5120.5625 -27.5863) 
(list 5194.585 -27.6363) 
(list 5194.585 -27.4593) 
(list 5120.5625 -27.5093)))
(apply 'command (append '("pline") coords '("c")))
(setq currobj (ssadd (entlast) currobj))
(setq coords (list 
(list 5120.5625 -27.3663) 
(list 5194.585 -27.3163) 
(list 5194.585 -27.1393) 
(list 5120.5625 -27.2893)))
(apply 'command (append '("pline") coords '("c")))
(setq currobj (ssadd (entlast) currobj))
(setq coords (list 
(list 5120.5625 -27.1463) 
(list 5194.585 -26.9963) 
(list 5194.585 -26.8193) 
(list 5120.5625 -27.0693)))
(apply 'command (append '("pline") coords '("c")))
(setq currobj (ssadd (entlast) currobj))
(setq coords (list 
(list 5120.5625 -26.9263) 
(list 5194.585 -26.6763) 
(list 5194.585 -26.4993) 
(list 5120.5625 -26.8493)))
(apply 'command (append '("pline") coords '("c")))
(setq currobj (ssadd (entlast) currobj))
(setq coords (list 
(list 5120.5625 -26.7063) 
(list 5194.585 -26.3563) 
(list 5194.585 -26.1793) 
(list 5120.5625 -26.6293)))
(apply 'command (append '("pline") coords '("c")))
(setq currobj (ssadd (entlast) currobj))
(setq coords (list 
(list 5120.5625 -26.4863) 
(list 5194.585 -26.0363) 
(list 5194.585 -25.8593) 
(list 5120.5625 -26.4093)))
(apply 'command (append '("pline") coords '("c")))
(setq currobj (ssadd (entlast) currobj))
(setq coords (list 
(list 5120.5625 -26.2663) 
(list 5194.585 -25.7163) 
(list 5194.585 -25.5393) 
(list 5120.5625 -26.1893)))
(apply 'command (append '("pline") coords '("c")))
(setq currobj (ssadd (entlast) currobj))
(setq coords (list 
(list 5120.5625 -26.0463) 
(list 5194.585 -25.3963) 
(list 5194.585 -25.2193) 
(list 5120.5625 -25.9693)))
(apply 'command (append '("pline") coords '("c")))
(setq currobj (ssadd (entlast) currobj))
(setq coords (list 
(list 5119.4375 -25.9693) 
(list 5045.415 -25.2193) 
(list 5045.415 -25.3963) 
(list 5119.4375 -26.0463)))
(apply 'command (append '("pline") coords '("c")))
(setq currobj (ssadd (entlast) currobj))
(setq coords (list 
(list 5119.4375 -26.1893) 
(list 5045.415 -25.5393) 
(list 5045.415 -25.7163) 
(list 5119.4375 -26.2663)))
(apply 'command (append '("pline") coords '("c")))
(setq currobj (ssadd (entlast) currobj))
(setq coords (list 
(list 5119.4375 -26.4093) 
(list 5045.415 -25.8593) 
(list 5045.415 -26.0363) 
(list 5119.4375 -26.4863)))
(apply 'command (append '("pline") coords '("c")))
(setq currobj (ssadd (entlast) currobj))
(setq coords (list 
(list 5119.4375 -26.6293) 
(list 5045.415 -26.1793) 
(list 5045.415 -26.3563) 
(list 5119.4375 -26.7063)))
(apply 'command (append '("pline") coords '("c")))
(setq currobj (ssadd (entlast) currobj))
(setq coords (list 
(list 5119.4375 -26.8493) 
(list 5045.415 -26.4993) 
(list 5045.415 -26.6763) 
(list 5119.4375 -26.9263)))
(apply 'command (append '("pline") coords '("c")))
(setq currobj (ssadd (entlast) currobj))
(setq coords (list 
(list 5119.4375 -27.0693) 
(list 5045.415 -26.8193) 
(list 5045.415 -26.9963) 
(list 5119.4375 -27.1463)))
(apply 'command (append '("pline") coords '("c")))
(setq currobj (ssadd (entlast) currobj))
(setq coords (list 
(list 5119.4375 -27.2893) 
(list 5045.415 -27.1393) 
(list 5045.415 -27.3163) 
(list 5119.4375 -27.3663)))
(apply 'command (append '("pline") coords '("c")))
(setq currobj (ssadd (entlast) currobj))
(setq coords (list 
(list 5119.4375 -27.5093) 
(list 5045.415 -27.4593) 
(list 5045.415 -27.6363) 
(list 5119.4375 -27.5863)))
(apply 'command (append '("pline") coords '("c")))
(setq currobj (ssadd (entlast) currobj))
(setq coords (list 
(list 5119.4375 -27.7293) 
(list 5045.415 -27.7793) 
(list 5045.415 -27.9563) 
(list 5119.4375 -27.8063)))
(apply 'command (append '("pline") coords '("c")))
(setq currobj (ssadd (entlast) currobj))
(setq coords (list 
(list 5119.4375 -27.9493) 
(list 5045.415 -28.0993) 
(list 5045.415 -28.2763) 
(list 5119.4375 -28.0263)))
(apply 'command (append '("pline") coords '("c")))
(setq currobj (ssadd (entlast) currobj))
(setq coords (list 
(list 5119.4375 -28.1693) 
(list 5045.415 -28.4193) 
(list 5045.415 -28.5963) 
(list 5119.4375 -28.2463)))
(apply 'command (append '("pline") coords '("c")))
(setq currobj (ssadd (entlast) currobj))
(setq coords (list 
(list 5119.4375 -28.3893) 
(list 5045.415 -28.7393) 
(list 5045.415 -28.9163) 
(list 5119.4375 -28.4663)))
(apply 'command (append '("pline") coords '("c")))
(setq currobj (ssadd (entlast) currobj))
(setq coords (list 
(list 5119.4375 -28.6093) 
(list 5045.415 -29.0593) 
(list 5045.415 -29.2363) 
(list 5119.4375 -28.6863)))
(apply 'command (append '("pline") coords '("c")))
(setq currobj (ssadd (entlast) currobj))
(setq coords (list 
(list 5119.4375 -28.8293) 
(list 5045.415 -29.3793) 
(list 5045.415 -29.5563) 
(list 5119.4375 -28.9063)))
(apply 'command (append '("pline") coords '("c")))
(setq currobj (ssadd (entlast) currobj))
(setq coords (list 
(list 5119.4375 -29.0493) 
(list 5045.415 -29.6993) 
(list 5045.415 -29.8763) 
(list 5119.4375 -29.1263)))
(apply 'command (append '("pline") coords '("c")))
(setq currobj (ssadd (entlast) currobj))
(command "_layer" "set" "nitride" "")
(command "_layer" "set" "text" "")
(command "_circle" "5119.0625,-40.2693" "0.075")
(command "_circle" "5119.0625,-39.9693" "0.075")
(command "_circle" "5119.0625,-39.6693" "0.075")
(command "_circle" "5119.0625,-39.3693" "0.075")
(command "_circle" "5119.0625,-39.0693" "0.075")
(command "_circle" "5118.7625,-40.2693" "0.075")
(command "_circle" "5118.7625,-39.9693" "0.075")
(command "_circle" "5118.7625,-39.6693" "0.075")
(command "_circle" "5118.7625,-39.3693" "0.075")
(command "_circle" "5118.7625,-39.0693" "0.075")
(command "_circle" "5118.4625,-40.2693" "0.075")
(command "_circle" "5118.4625,-39.9693" "0.075")
(command "_circle" "5118.4625,-39.6693" "0.075")
(command "_circle" "5118.4625,-39.3693" "0.075")
(command "_circle" "5118.4625,-39.0693" "0.075")
(command "_circle" "5118.1625,-40.2693" "0.075")
(command "_circle" "5118.1625,-39.9693" "0.075")
(command "_circle" "5118.1625,-39.6693" "0.075")
(command "_circle" "5118.1625,-39.3693" "0.075")
(command "_circle" "5118.1625,-39.0693" "0.075")
(command "_circle" "5117.8625,-40.2693" "0.075")
(command "_circle" "5117.8625,-39.9693" "0.075")
(command "_circle" "5117.8625,-39.6693" "0.075")
(command "_circle" "5117.8625,-39.3693" "0.075")
(command "_circle" "5117.8625,-39.0693" "0.075")
(command "_layer" "set" "nitride" "")
(setq coords (list 
(list 5120.2625 -14.8263) 
(list 5120.2625 100.8184) 
(list 5119.7375 100.8184) 
(list 5119.7375 -14.8263)))
(apply 'command (append '("pline") coords '("c")))
(setq currobj (ssadd (entlast) currobj))
(command "_layer" "set" "prebias" "")
(command "_rectangle" "5119.7375,-14.8263" "5120.2625,100.8184")
(setq currobj (ssadd (entlast) currobj))
(command "_layer" "set" "nitride" "")
(setq coords (list 
(list 5120.2625 100.8184) 
(list 5120.5625 110.8184) 
(list 5120.5625 110.8184) 
(list 5120.5625 111.8184) 
(list 5194.585 111.0684) 
(list 5194.585 116.0114) 
(list 5120.5625 115.2614) 
(list 5120.5625 116.2614) 
(list 5120.5625 116.2614) 
(list 5120.2625 126.2614) 
(list 5119.7375 126.2614) 
(list 5119.4375 116.2614) 
(list 5119.4375 116.2614) 
(list 5119.4375 115.2614) 
(list 5045.415 116.0114) 
(list 5045.415 111.0684) 
(list 5119.4375 111.8184) 
(list 5119.4375 110.8184) 
(list 5119.4375 110.8184) 
(list 5119.7375 100.8184)))
(apply 'command (append '("pline") coords '("c")))
(setq currobj (ssadd (entlast) currobj))
(command "_layer" "set" "prebias" "")
(setq coords (list 
(list 5119.4375 100.8184) 
(list 5119.4375 111.8184) 
(list 5045.415 111.0684) 
(list 5045.415 116.0114) 
(list 5119.4375 115.2614) 
(list 5119.4375 126.2614) 
(list 5120.5625 126.2614) 
(list 5120.5625 115.2614) 
(list 5194.585 116.0114) 
(list 5194.585 111.0684) 
(list 5120.5625 111.8184) 
(list 5120.5625 100.8184)))
(apply 'command (append '("pline") coords '("c")))
(setq currobj (ssadd (entlast) currobj))
(command "_layer" "set" "nitride" "")
(command "_layer" "set" "fda1" "")
(setq coords (list 
(list 5120.5625 111.9614) 
(list 5194.585 111.2114) 
(list 5194.585 111.3884) 
(list 5120.5625 112.0384)))
(apply 'command (append '("pline") coords '("c")))
(setq currobj (ssadd (entlast) currobj))
(setq coords (list 
(list 5120.5625 112.1814) 
(list 5194.585 111.5314) 
(list 5194.585 111.7084) 
(list 5120.5625 112.2584)))
(apply 'command (append '("pline") coords '("c")))
(setq currobj (ssadd (entlast) currobj))
(setq coords (list 
(list 5120.5625 112.4014) 
(list 5194.585 111.8514) 
(list 5194.585 112.0284) 
(list 5120.5625 112.4784)))
(apply 'command (append '("pline") coords '("c")))
(setq currobj (ssadd (entlast) currobj))
(setq coords (list 
(list 5120.5625 112.6214) 
(list 5194.585 112.1714) 
(list 5194.585 112.3484) 
(list 5120.5625 112.6984)))
(apply 'command (append '("pline") coords '("c")))
(setq currobj (ssadd (entlast) currobj))
(setq coords (list 
(list 5120.5625 112.8414) 
(list 5194.585 112.4914) 
(list 5194.585 112.6684) 
(list 5120.5625 112.9184)))
(apply 'command (append '("pline") coords '("c")))
(setq currobj (ssadd (entlast) currobj))
(setq coords (list 
(list 5120.5625 113.0614) 
(list 5194.585 112.8114) 
(list 5194.585 112.9884) 
(list 5120.5625 113.1384)))
(apply 'command (append '("pline") coords '("c")))
(setq currobj (ssadd (entlast) currobj))
(setq coords (list 
(list 5120.5625 113.2814) 
(list 5194.585 113.1314) 
(list 5194.585 113.3084) 
(list 5120.5625 113.3584)))
(apply 'command (append '("pline") coords '("c")))
(setq currobj (ssadd (entlast) currobj))
(setq coords (list 
(list 5120.5625 113.5014) 
(list 5194.585 113.4514) 
(list 5194.585 113.6284) 
(list 5120.5625 113.5784)))
(apply 'command (append '("pline") coords '("c")))
(setq currobj (ssadd (entlast) currobj))
(setq coords (list 
(list 5120.5625 113.7214) 
(list 5194.585 113.7714) 
(list 5194.585 113.9484) 
(list 5120.5625 113.7984)))
(apply 'command (append '("pline") coords '("c")))
(setq currobj (ssadd (entlast) currobj))
(setq coords (list 
(list 5120.5625 113.9414) 
(list 5194.585 114.0914) 
(list 5194.585 114.2684) 
(list 5120.5625 114.0184)))
(apply 'command (append '("pline") coords '("c")))
(setq currobj (ssadd (entlast) currobj))
(setq coords (list 
(list 5120.5625 114.1614) 
(list 5194.585 114.4114) 
(list 5194.585 114.5884) 
(list 5120.5625 114.2384)))
(apply 'command (append '("pline") coords '("c")))
(setq currobj (ssadd (entlast) currobj))
(setq coords (list 
(list 5120.5625 114.3814) 
(list 5194.585 114.7314) 
(list 5194.585 114.9084) 
(list 5120.5625 114.4584)))
(apply 'command (append '("pline") coords '("c")))
(setq currobj (ssadd (entlast) currobj))
(setq coords (list 
(list 5120.5625 114.6014) 
(list 5194.585 115.0514) 
(list 5194.585 115.2284) 
(list 5120.5625 114.6784)))
(apply 'command (append '("pline") coords '("c")))
(setq currobj (ssadd (entlast) currobj))
(setq coords (list 
(list 5120.5625 114.8214) 
(list 5194.585 115.3714) 
(list 5194.585 115.5484) 
(list 5120.5625 114.8984)))
(apply 'command (append '("pline") coords '("c")))
(setq currobj (ssadd (entlast) currobj))
(setq coords (list 
(list 5120.5625 115.0414) 
(list 5194.585 115.6914) 
(list 5194.585 115.8684) 
(list 5120.5625 115.1184)))
(apply 'command (append '("pline") coords '("c")))
(setq currobj (ssadd (entlast) currobj))
(setq coords (list 
(list 5119.4375 115.1184) 
(list 5045.415 115.8684) 
(list 5045.415 115.6914) 
(list 5119.4375 115.0414)))
(apply 'command (append '("pline") coords '("c")))
(setq currobj (ssadd (entlast) currobj))
(setq coords (list 
(list 5119.4375 114.8984) 
(list 5045.415 115.5484) 
(list 5045.415 115.3714) 
(list 5119.4375 114.8214)))
(apply 'command (append '("pline") coords '("c")))
(setq currobj (ssadd (entlast) currobj))
(setq coords (list 
(list 5119.4375 114.6784) 
(list 5045.415 115.2284) 
(list 5045.415 115.0514) 
(list 5119.4375 114.6014)))
(apply 'command (append '("pline") coords '("c")))
(setq currobj (ssadd (entlast) currobj))
(setq coords (list 
(list 5119.4375 114.4584) 
(list 5045.415 114.9084) 
(list 5045.415 114.7314) 
(list 5119.4375 114.3814)))
(apply 'command (append '("pline") coords '("c")))
(setq currobj (ssadd (entlast) currobj))
(setq coords (list 
(list 5119.4375 114.2384) 
(list 5045.415 114.5884) 
(list 5045.415 114.4114) 
(list 5119.4375 114.1614)))
(apply 'command (append '("pline") coords '("c")))
(setq currobj (ssadd (entlast) currobj))
(setq coords (list 
(list 5119.4375 114.0184) 
(list 5045.415 114.2684) 
(list 5045.415 114.0914) 
(list 5119.4375 113.9414)))
(apply 'command (append '("pline") coords '("c")))
(setq currobj (ssadd (entlast) currobj))
(setq coords (list 
(list 5119.4375 113.7984) 
(list 5045.415 113.9484) 
(list 5045.415 113.7714) 
(list 5119.4375 113.7214)))
(apply 'command (append '("pline") coords '("c")))
(setq currobj (ssadd (entlast) currobj))
(setq coords (list 
(list 5119.4375 113.5784) 
(list 5045.415 113.6284) 
(list 5045.415 113.4514) 
(list 5119.4375 113.5014)))
(apply 'command (append '("pline") coords '("c")))
(setq currobj (ssadd (entlast) currobj))
(setq coords (list 
(list 5119.4375 113.3584) 
(list 5045.415 113.3084) 
(list 5045.415 113.1314) 
(list 5119.4375 113.2814)))
(apply 'command (append '("pline") coords '("c")))
(setq currobj (ssadd (entlast) currobj))
(setq coords (list 
(list 5119.4375 113.1384) 
(list 5045.415 112.9884) 
(list 5045.415 112.8114) 
(list 5119.4375 113.0614)))
(apply 'command (append '("pline") coords '("c")))
(setq currobj (ssadd (entlast) currobj))
(setq coords (list 
(list 5119.4375 112.9184) 
(list 5045.415 112.6684) 
(list 5045.415 112.4914) 
(list 5119.4375 112.8414)))
(apply 'command (append '("pline") coords '("c")))
(setq currobj (ssadd (entlast) currobj))
(setq coords (list 
(list 5119.4375 112.6984) 
(list 5045.415 112.3484) 
(list 5045.415 112.1714) 
(list 5119.4375 112.6214)))
(apply 'command (append '("pline") coords '("c")))
(setq currobj (ssadd (entlast) currobj))
(setq coords (list 
(list 5119.4375 112.4784) 
(list 5045.415 112.0284) 
(list 5045.415 111.8514) 
(list 5119.4375 112.4014)))
(apply 'command (append '("pline") coords '("c")))
(setq currobj (ssadd (entlast) currobj))
(setq coords (list 
(list 5119.4375 112.2584) 
(list 5045.415 111.7084) 
(list 5045.415 111.5314) 
(list 5119.4375 112.1814)))
(apply 'command (append '("pline") coords '("c")))
(setq currobj (ssadd (entlast) currobj))
(setq coords (list 
(list 5119.4375 112.0384) 
(list 5045.415 111.3884) 
(list 5045.415 111.2114) 
(list 5119.4375 111.9614)))
(apply 'command (append '("pline") coords '("c")))
(setq currobj (ssadd (entlast) currobj))
(command "_layer" "set" "nitride" "")
(command "_layer" "set" "text" "")
(command "_circle" "5119.0625,100.8184" "0.075")
(command "_circle" "5119.0625,101.1184" "0.075")
(command "_circle" "5119.0625,101.4184" "0.075")
(command "_circle" "5119.0625,101.7184" "0.075")
(command "_circle" "5119.0625,102.0184" "0.075")
(command "_circle" "5118.7625,100.8184" "0.075")
(command "_circle" "5118.7625,101.1184" "0.075")
(command "_circle" "5118.7625,101.4184" "0.075")
(command "_circle" "5118.7625,101.7184" "0.075")
(command "_circle" "5118.7625,102.0184" "0.075")
(command "_circle" "5118.4625,100.8184" "0.075")
(command "_circle" "5118.4625,101.1184" "0.075")
(command "_circle" "5118.4625,101.4184" "0.075")
(command "_circle" "5118.4625,101.7184" "0.075")
(command "_circle" "5118.4625,102.0184" "0.075")
(command "_circle" "5118.1625,100.8184" "0.075")
(command "_circle" "5118.1625,101.1184" "0.075")
(command "_circle" "5118.1625,101.4184" "0.075")
(command "_circle" "5118.1625,101.7184" "0.075")
(command "_circle" "5118.1625,102.0184" "0.075")
(command "_circle" "5117.8625,100.8184" "0.075")
(command "_circle" "5117.8625,101.1184" "0.075")
(command "_circle" "5117.8625,101.4184" "0.075")
(command "_circle" "5117.8625,101.7184" "0.075")
(command "_circle" "5117.8625,102.0184" "0.075")
(command "_layer" "set" "nitride" "")
(setq coords (list 
(list 5120.2625 126.2614) 
(list 5120.2625 241.9061) 
(list 5119.7375 241.9061) 
(list 5119.7375 126.2614)))
(apply 'command (append '("pline") coords '("c")))
(setq currobj (ssadd (entlast) currobj))
(command "_layer" "set" "prebias" "")
(command "_rectangle" "5119.7375,126.2614" "5120.2625,241.9061")
(setq currobj (ssadd (entlast) currobj))
(command "_layer" "set" "nitride" "")
(setq coords (list 
(list 5120.2625 241.9061) 
(list 5120.5625 251.9061) 
(list 5120.5625 251.9061) 
(list 5120.5625 252.9061) 
(list 5194.585 252.1561) 
(list 5194.585 257.0991) 
(list 5120.5625 256.3491) 
(list 5120.5625 257.3491) 
(list 5120.5625 257.3491) 
(list 5120.2625 267.3491) 
(list 5119.7375 267.3491) 
(list 5119.4375 257.3491) 
(list 5119.4375 257.3491) 
(list 5119.4375 256.3491) 
(list 5045.415 257.0991) 
(list 5045.415 252.1561) 
(list 5119.4375 252.9061) 
(list 5119.4375 251.9061) 
(list 5119.4375 251.9061) 
(list 5119.7375 241.9061)))
(apply 'command (append '("pline") coords '("c")))
(setq currobj (ssadd (entlast) currobj))
(command "_layer" "set" "prebias" "")
(setq coords (list 
(list 5119.4375 241.9061) 
(list 5119.4375 252.9061) 
(list 5045.415 252.1561) 
(list 5045.415 257.0991) 
(list 5119.4375 256.3491) 
(list 5119.4375 267.3491) 
(list 5120.5625 267.3491) 
(list 5120.5625 256.3491) 
(list 5194.585 257.0991) 
(list 5194.585 252.1561) 
(list 5120.5625 252.9061) 
(list 5120.5625 241.9061)))
(apply 'command (append '("pline") coords '("c")))
(setq currobj (ssadd (entlast) currobj))
(command "_layer" "set" "nitride" "")
(command "_layer" "set" "fda1" "")
(setq coords (list 
(list 5120.5625 253.0491) 
(list 5194.585 252.2991) 
(list 5194.585 252.4761) 
(list 5120.5625 253.1261)))
(apply 'command (append '("pline") coords '("c")))
(setq currobj (ssadd (entlast) currobj))
(setq coords (list 
(list 5120.5625 253.2691) 
(list 5194.585 252.6191) 
(list 5194.585 252.7961) 
(list 5120.5625 253.3461)))
(apply 'command (append '("pline") coords '("c")))
(setq currobj (ssadd (entlast) currobj))
(setq coords (list 
(list 5120.5625 253.4891) 
(list 5194.585 252.9391) 
(list 5194.585 253.1161) 
(list 5120.5625 253.5661)))
(apply 'command (append '("pline") coords '("c")))
(setq currobj (ssadd (entlast) currobj))
(setq coords (list 
(list 5120.5625 253.7091) 
(list 5194.585 253.2591) 
(list 5194.585 253.4361) 
(list 5120.5625 253.7861)))
(apply 'command (append '("pline") coords '("c")))
(setq currobj (ssadd (entlast) currobj))
(setq coords (list 
(list 5120.5625 253.9291) 
(list 5194.585 253.5791) 
(list 5194.585 253.7561) 
(list 5120.5625 254.0061)))
(apply 'command (append '("pline") coords '("c")))
(setq currobj (ssadd (entlast) currobj))
(setq coords (list 
(list 5120.5625 254.1491) 
(list 5194.585 253.8991) 
(list 5194.585 254.0761) 
(list 5120.5625 254.2261)))
(apply 'command (append '("pline") coords '("c")))
(setq currobj (ssadd (entlast) currobj))
(setq coords (list 
(list 5120.5625 254.3691) 
(list 5194.585 254.2191) 
(list 5194.585 254.3961) 
(list 5120.5625 254.4461)))
(apply 'command (append '("pline") coords '("c")))
(setq currobj (ssadd (entlast) currobj))
(setq coords (list 
(list 5120.5625 254.5891) 
(list 5194.585 254.5391) 
(list 5194.585 254.7161) 
(list 5120.5625 254.6661)))
(apply 'command (append '("pline") coords '("c")))
(setq currobj (ssadd (entlast) currobj))
(setq coords (list 
(list 5120.5625 254.8091) 
(list 5194.585 254.8591) 
(list 5194.585 255.0361) 
(list 5120.5625 254.8861)))
(apply 'command (append '("pline") coords '("c")))
(setq currobj (ssadd (entlast) currobj))
(setq coords (list 
(list 5120.5625 255.0291) 
(list 5194.585 255.1791) 
(list 5194.585 255.3561) 
(list 5120.5625 255.1061)))
(apply 'command (append '("pline") coords '("c")))
(setq currobj (ssadd (entlast) currobj))
(setq coords (list 
(list 5120.5625 255.2491) 
(list 5194.585 255.4991) 
(list 5194.585 255.6761) 
(list 5120.5625 255.3261)))
(apply 'command (append '("pline") coords '("c")))
(setq currobj (ssadd (entlast) currobj))
(setq coords (list 
(list 5120.5625 255.4691) 
(list 5194.585 255.8191) 
(list 5194.585 255.9961) 
(list 5120.5625 255.5461)))
(apply 'command (append '("pline") coords '("c")))
(setq currobj (ssadd (entlast) currobj))
(setq coords (list 
(list 5120.5625 255.6891) 
(list 5194.585 256.1391) 
(list 5194.585 256.3161) 
(list 5120.5625 255.7661)))
(apply 'command (append '("pline") coords '("c")))
(setq currobj (ssadd (entlast) currobj))
(setq coords (list 
(list 5120.5625 255.9091) 
(list 5194.585 256.4591) 
(list 5194.585 256.6361) 
(list 5120.5625 255.9861)))
(apply 'command (append '("pline") coords '("c")))
(setq currobj (ssadd (entlast) currobj))
(setq coords (list 
(list 5120.5625 256.1291) 
(list 5194.585 256.7791) 
(list 5194.585 256.9561) 
(list 5120.5625 256.2061)))
(apply 'command (append '("pline") coords '("c")))
(setq currobj (ssadd (entlast) currobj))
(setq coords (list 
(list 5119.4375 256.2061) 
(list 5045.415 256.9561) 
(list 5045.415 256.7791) 
(list 5119.4375 256.1291)))
(apply 'command (append '("pline") coords '("c")))
(setq currobj (ssadd (entlast) currobj))
(setq coords (list 
(list 5119.4375 255.9861) 
(list 5045.415 256.6361) 
(list 5045.415 256.4591) 
(list 5119.4375 255.9091)))
(apply 'command (append '("pline") coords '("c")))
(setq currobj (ssadd (entlast) currobj))
(setq coords (list 
(list 5119.4375 255.7661) 
(list 5045.415 256.3161) 
(list 5045.415 256.1391) 
(list 5119.4375 255.6891)))
(apply 'command (append '("pline") coords '("c")))
(setq currobj (ssadd (entlast) currobj))
(setq coords (list 
(list 5119.4375 255.5461) 
(list 5045.415 255.9961) 
(list 5045.415 255.8191) 
(list 5119.4375 255.4691)))
(apply 'command (append '("pline") coords '("c")))
(setq currobj (ssadd (entlast) currobj))
(setq coords (list 
(list 5119.4375 255.3261) 
(list 5045.415 255.6761) 
(list 5045.415 255.4991) 
(list 5119.4375 255.2491)))
(apply 'command (append '("pline") coords '("c")))
(setq currobj (ssadd (entlast) currobj))
(setq coords (list 
(list 5119.4375 255.1061) 
(list 5045.415 255.3561) 
(list 5045.415 255.1791) 
(list 5119.4375 255.0291)))
(apply 'command (append '("pline") coords '("c")))
(setq currobj (ssadd (entlast) currobj))
(setq coords (list 
(list 5119.4375 254.8861) 
(list 5045.415 255.0361) 
(list 5045.415 254.8591) 
(list 5119.4375 254.8091)))
(apply 'command (append '("pline") coords '("c")))
(setq currobj (ssadd (entlast) currobj))
(setq coords (list 
(list 5119.4375 254.6661) 
(list 5045.415 254.7161) 
(list 5045.415 254.5391) 
(list 5119.4375 254.5891)))
(apply 'command (append '("pline") coords '("c")))
(setq currobj (ssadd (entlast) currobj))
(setq coords (list 
(list 5119.4375 254.4461) 
(list 5045.415 254.3961) 
(list 5045.415 254.2191) 
(list 5119.4375 254.3691)))
(apply 'command (append '("pline") coords '("c")))
(setq currobj (ssadd (entlast) currobj))
(setq coords (list 
(list 5119.4375 254.2261) 
(list 5045.415 254.0761) 
(list 5045.415 253.8991) 
(list 5119.4375 254.1491)))
(apply 'command (append '("pline") coords '("c")))
(setq currobj (ssadd (entlast) currobj))
(setq coords (list 
(list 5119.4375 254.0061) 
(list 5045.415 253.7561) 
(list 5045.415 253.5791) 
(list 5119.4375 253.9291)))
(apply 'command (append '("pline") coords '("c")))
(setq currobj (ssadd (entlast) currobj))
(setq coords (list 
(list 5119.4375 253.7861) 
(list 5045.415 253.4361) 
(list 5045.415 253.2591) 
(list 5119.4375 253.7091)))
(apply 'command (append '("pline") coords '("c")))
(setq currobj (ssadd (entlast) currobj))
(setq coords (list 
(list 5119.4375 253.5661) 
(list 5045.415 253.1161) 
(list 5045.415 252.9391) 
(list 5119.4375 253.4891)))
(apply 'command (append '("pline") coords '("c")))
(setq currobj (ssadd (entlast) currobj))
(setq coords (list 
(list 5119.4375 253.3461) 
(list 5045.415 252.7961) 
(list 5045.415 252.6191) 
(list 5119.4375 253.2691)))
(apply 'command (append '("pline") coords '("c")))
(setq currobj (ssadd (entlast) currobj))
(setq coords (list 
(list 5119.4375 253.1261) 
(list 5045.415 252.4761) 
(list 5045.415 252.2991) 
(list 5119.4375 253.0491)))
(apply 'command (append '("pline") coords '("c")))
(setq currobj (ssadd (entlast) currobj))
(command "_layer" "set" "nitride" "")
(command "_layer" "set" "text" "")
(command "_circle" "5119.0625,241.9061" "0.075")
(command "_circle" "5119.0625,242.2061" "0.075")
(command "_circle" "5119.0625,242.5061" "0.075")
(command "_circle" "5119.0625,242.8061" "0.075")
(command "_circle" "5119.0625,243.1061" "0.075")
(command "_circle" "5118.7625,241.9061" "0.075")
(command "_circle" "5118.7625,242.2061" "0.075")
(command "_circle" "5118.7625,242.5061" "0.075")
(command "_circle" "5118.7625,242.8061" "0.075")
(command "_circle" "5118.7625,243.1061" "0.075")
(command "_circle" "5118.4625,241.9061" "0.075")
(command "_circle" "5118.4625,242.2061" "0.075")
(command "_circle" "5118.4625,242.5061" "0.075")
(command "_circle" "5118.4625,242.8061" "0.075")
(command "_circle" "5118.4625,243.1061" "0.075")
(command "_circle" "5118.1625,241.9061" "0.075")
(command "_circle" "5118.1625,242.2061" "0.075")
(command "_circle" "5118.1625,242.5061" "0.075")
(command "_circle" "5118.1625,242.8061" "0.075")
(command "_circle" "5118.1625,243.1061" "0.075")
(command "_circle" "5117.8625,241.9061" "0.075")
(command "_circle" "5117.8625,242.2061" "0.075")
(command "_circle" "5117.8625,242.5061" "0.075")
(command "_circle" "5117.8625,242.8061" "0.075")
(command "_circle" "5117.8625,243.1061" "0.075")
(command "_layer" "set" "nitride" "")
(setq coords (list 
(list 5120.2625 267.3491) 
(list 5120.2625 382.9939) 
(list 5119.7375 382.9939) 
(list 5119.7375 267.3491)))
(apply 'command (append '("pline") coords '("c")))
(setq currobj (ssadd (entlast) currobj))
(command "_layer" "set" "prebias" "")
(command "_rectangle" "5119.7375,267.3491" "5120.2625,382.9939")
(setq currobj (ssadd (entlast) currobj))
(command "_layer" "set" "nitride" "")
(setq coords (list 
(list 5120.2625 382.9939) 
(list 5120.5625 392.9939) 
(list 5120.5625 392.9939) 
(list 5120.5625 393.9939) 
(list 5194.585 393.2439) 
(list 5194.585 398.1869) 
(list 5120.5625 397.4369) 
(list 5120.5625 398.4369) 
(list 5120.5625 398.4369) 
(list 5120.2625 408.4369) 
(list 5119.7375 408.4369) 
(list 5119.4375 398.4369) 
(list 5119.4375 398.4369) 
(list 5119.4375 397.4369) 
(list 5045.415 398.1869) 
(list 5045.415 393.2439) 
(list 5119.4375 393.9939) 
(list 5119.4375 392.9939) 
(list 5119.4375 392.9939) 
(list 5119.7375 382.9939)))
(apply 'command (append '("pline") coords '("c")))
(setq currobj (ssadd (entlast) currobj))
(command "_layer" "set" "prebias" "")
(setq coords (list 
(list 5119.4375 382.9939) 
(list 5119.4375 393.9939) 
(list 5045.415 393.2439) 
(list 5045.415 398.1869) 
(list 5119.4375 397.4369) 
(list 5119.4375 408.4369) 
(list 5120.5625 408.4369) 
(list 5120.5625 397.4369) 
(list 5194.585 398.1869) 
(list 5194.585 393.2439) 
(list 5120.5625 393.9939) 
(list 5120.5625 382.9939)))
(apply 'command (append '("pline") coords '("c")))
(setq currobj (ssadd (entlast) currobj))
(command "_layer" "set" "nitride" "")
(command "_layer" "set" "fda1" "")
(setq coords (list 
(list 5120.5625 394.1369) 
(list 5194.585 393.3869) 
(list 5194.585 393.5639) 
(list 5120.5625 394.2139)))
(apply 'command (append '("pline") coords '("c")))
(setq currobj (ssadd (entlast) currobj))
(setq coords (list 
(list 5120.5625 394.3569) 
(list 5194.585 393.7069) 
(list 5194.585 393.8839) 
(list 5120.5625 394.4339)))
(apply 'command (append '("pline") coords '("c")))
(setq currobj (ssadd (entlast) currobj))
(setq coords (list 
(list 5120.5625 394.5769) 
(list 5194.585 394.0269) 
(list 5194.585 394.2039) 
(list 5120.5625 394.6539)))
(apply 'command (append '("pline") coords '("c")))
(setq currobj (ssadd (entlast) currobj))
(setq coords (list 
(list 5120.5625 394.7969) 
(list 5194.585 394.3469) 
(list 5194.585 394.5239) 
(list 5120.5625 394.8739)))
(apply 'command (append '("pline") coords '("c")))
(setq currobj (ssadd (entlast) currobj))
(setq coords (list 
(list 5120.5625 395.0169) 
(list 5194.585 394.6669) 
(list 5194.585 394.8439) 
(list 5120.5625 395.0939)))
(apply 'command (append '("pline") coords '("c")))
(setq currobj (ssadd (entlast) currobj))
(setq coords (list 
(list 5120.5625 395.2369) 
(list 5194.585 394.9869) 
(list 5194.585 395.1639) 
(list 5120.5625 395.3139)))
(apply 'command (append '("pline") coords '("c")))
(setq currobj (ssadd (entlast) currobj))
(setq coords (list 
(list 5120.5625 395.4569) 
(list 5194.585 395.3069) 
(list 5194.585 395.4839) 
(list 5120.5625 395.5339)))
(apply 'command (append '("pline") coords '("c")))
(setq currobj (ssadd (entlast) currobj))
(setq coords (list 
(list 5120.5625 395.6769) 
(list 5194.585 395.6269) 
(list 5194.585 395.8039) 
(list 5120.5625 395.7539)))
(apply 'command (append '("pline") coords '("c")))
(setq currobj (ssadd (entlast) currobj))
(setq coords (list 
(list 5120.5625 395.8969) 
(list 5194.585 395.9469) 
(list 5194.585 396.1239) 
(list 5120.5625 395.9739)))
(apply 'command (append '("pline") coords '("c")))
(setq currobj (ssadd (entlast) currobj))
(setq coords (list 
(list 5120.5625 396.1169) 
(list 5194.585 396.2669) 
(list 5194.585 396.4439) 
(list 5120.5625 396.1939)))
(apply 'command (append '("pline") coords '("c")))
(setq currobj (ssadd (entlast) currobj))
(setq coords (list 
(list 5120.5625 396.3369) 
(list 5194.585 396.5869) 
(list 5194.585 396.7639) 
(list 5120.5625 396.4139)))
(apply 'command (append '("pline") coords '("c")))
(setq currobj (ssadd (entlast) currobj))
(setq coords (list 
(list 5120.5625 396.5569) 
(list 5194.585 396.9069) 
(list 5194.585 397.0839) 
(list 5120.5625 396.6339)))
(apply 'command (append '("pline") coords '("c")))
(setq currobj (ssadd (entlast) currobj))
(setq coords (list 
(list 5120.5625 396.7769) 
(list 5194.585 397.2269) 
(list 5194.585 397.4039) 
(list 5120.5625 396.8539)))
(apply 'command (append '("pline") coords '("c")))
(setq currobj (ssadd (entlast) currobj))
(setq coords (list 
(list 5120.5625 396.9969) 
(list 5194.585 397.5469) 
(list 5194.585 397.7239) 
(list 5120.5625 397.0739)))
(apply 'command (append '("pline") coords '("c")))
(setq currobj (ssadd (entlast) currobj))
(setq coords (list 
(list 5120.5625 397.2169) 
(list 5194.585 397.8669) 
(list 5194.585 398.0439) 
(list 5120.5625 397.2939)))
(apply 'command (append '("pline") coords '("c")))
(setq currobj (ssadd (entlast) currobj))
(setq coords (list 
(list 5119.4375 397.2939) 
(list 5045.415 398.0439) 
(list 5045.415 397.8669) 
(list 5119.4375 397.2169)))
(apply 'command (append '("pline") coords '("c")))
(setq currobj (ssadd (entlast) currobj))
(setq coords (list 
(list 5119.4375 397.0739) 
(list 5045.415 397.7239) 
(list 5045.415 397.5469) 
(list 5119.4375 396.9969)))
(apply 'command (append '("pline") coords '("c")))
(setq currobj (ssadd (entlast) currobj))
(setq coords (list 
(list 5119.4375 396.8539) 
(list 5045.415 397.4039) 
(list 5045.415 397.2269) 
(list 5119.4375 396.7769)))
(apply 'command (append '("pline") coords '("c")))
(setq currobj (ssadd (entlast) currobj))
(setq coords (list 
(list 5119.4375 396.6339) 
(list 5045.415 397.0839) 
(list 5045.415 396.9069) 
(list 5119.4375 396.5569)))
(apply 'command (append '("pline") coords '("c")))
(setq currobj (ssadd (entlast) currobj))
(setq coords (list 
(list 5119.4375 396.4139) 
(list 5045.415 396.7639) 
(list 5045.415 396.5869) 
(list 5119.4375 396.3369)))
(apply 'command (append '("pline") coords '("c")))
(setq currobj (ssadd (entlast) currobj))
(setq coords (list 
(list 5119.4375 396.1939) 
(list 5045.415 396.4439) 
(list 5045.415 396.2669) 
(list 5119.4375 396.1169)))
(apply 'command (append '("pline") coords '("c")))
(setq currobj (ssadd (entlast) currobj))
(setq coords (list 
(list 5119.4375 395.9739) 
(list 5045.415 396.1239) 
(list 5045.415 395.9469) 
(list 5119.4375 395.8969)))
(apply 'command (append '("pline") coords '("c")))
(setq currobj (ssadd (entlast) currobj))
(setq coords (list 
(list 5119.4375 395.7539) 
(list 5045.415 395.8039) 
(list 5045.415 395.6269) 
(list 5119.4375 395.6769)))
(apply 'command (append '("pline") coords '("c")))
(setq currobj (ssadd (entlast) currobj))
(setq coords (list 
(list 5119.4375 395.5339) 
(list 5045.415 395.4839) 
(list 5045.415 395.3069) 
(list 5119.4375 395.4569)))
(apply 'command (append '("pline") coords '("c")))
(setq currobj (ssadd (entlast) currobj))
(setq coords (list 
(list 5119.4375 395.3139) 
(list 5045.415 395.1639) 
(list 5045.415 394.9869) 
(list 5119.4375 395.2369)))
(apply 'command (append '("pline") coords '("c")))
(setq currobj (ssadd (entlast) currobj))
(setq coords (list 
(list 5119.4375 395.0939) 
(list 5045.415 394.8439) 
(list 5045.415 394.6669) 
(list 5119.4375 395.0169)))
(apply 'command (append '("pline") coords '("c")))
(setq currobj (ssadd (entlast) currobj))
(setq coords (list 
(list 5119.4375 394.8739) 
(list 5045.415 394.5239) 
(list 5045.415 394.3469) 
(list 5119.4375 394.7969)))
(apply 'command (append '("pline") coords '("c")))
(setq currobj (ssadd (entlast) currobj))
(setq coords (list 
(list 5119.4375 394.6539) 
(list 5045.415 394.2039) 
(list 5045.415 394.0269) 
(list 5119.4375 394.5769)))
(apply 'command (append '("pline") coords '("c")))
(setq currobj (ssadd (entlast) currobj))
(setq coords (list 
(list 5119.4375 394.4339) 
(list 5045.415 393.8839) 
(list 5045.415 393.7069) 
(list 5119.4375 394.3569)))
(apply 'command (append '("pline") coords '("c")))
(setq currobj (ssadd (entlast) currobj))
(setq coords (list 
(list 5119.4375 394.2139) 
(list 5045.415 393.5639) 
(list 5045.415 393.3869) 
(list 5119.4375 394.1369)))
(apply 'command (append '("pline") coords '("c")))
(setq currobj (ssadd (entlast) currobj))
(command "_layer" "set" "nitride" "")
(command "_layer" "set" "text" "")
(command "_circle" "5119.0625,382.9939" "0.075")
(command "_circle" "5119.0625,383.2939" "0.075")
(command "_circle" "5119.0625,383.5939" "0.075")
(command "_circle" "5119.0625,383.8939" "0.075")
(command "_circle" "5119.0625,384.1939" "0.075")
(command "_circle" "5118.7625,382.9939" "0.075")
(command "_circle" "5118.7625,383.2939" "0.075")
(command "_circle" "5118.7625,383.5939" "0.075")
(command "_circle" "5118.7625,383.8939" "0.075")
(command "_circle" "5118.7625,384.1939" "0.075")
(command "_circle" "5118.4625,382.9939" "0.075")
(command "_circle" "5118.4625,383.2939" "0.075")
(command "_circle" "5118.4625,383.5939" "0.075")
(command "_circle" "5118.4625,383.8939" "0.075")
(command "_circle" "5118.4625,384.1939" "0.075")
(command "_circle" "5118.1625,382.9939" "0.075")
(command "_circle" "5118.1625,383.2939" "0.075")
(command "_circle" "5118.1625,383.5939" "0.075")
(command "_circle" "5118.1625,383.8939" "0.075")
(command "_circle" "5118.1625,384.1939" "0.075")
(command "_circle" "5117.8625,382.9939" "0.075")
(command "_circle" "5117.8625,383.2939" "0.075")
(command "_circle" "5117.8625,383.5939" "0.075")
(command "_circle" "5117.8625,383.8939" "0.075")
(command "_circle" "5117.8625,384.1939" "0.075")
(command "_layer" "set" "nitride" "")
(setq coords (list 
(list 5120.2625 408.4369) 
(list 5120.2625 524.0816) 
(list 5119.7375 524.0816) 
(list 5119.7375 408.4369)))
(apply 'command (append '("pline") coords '("c")))
(setq currobj (ssadd (entlast) currobj))
(command "_layer" "set" "prebias" "")
(command "_rectangle" "5119.7375,408.4369" "5120.2625,524.0816")
(setq currobj (ssadd (entlast) currobj))
(command "_layer" "set" "nitride" "")
(setq coords (list 
(list 5120.2625 524.0816) 
(list 5120.5625 534.0816) 
(list 5120.5625 534.0816) 
(list 5120.5625 535.0816) 
(list 5194.585 534.3316) 
(list 5194.585 539.2746) 
(list 5120.5625 538.5246) 
(list 5120.5625 539.5246) 
(list 5120.5625 539.5246) 
(list 5120.2625 549.5246) 
(list 5119.7375 549.5246) 
(list 5119.4375 539.5246) 
(list 5119.4375 539.5246) 
(list 5119.4375 538.5246) 
(list 5045.415 539.2746) 
(list 5045.415 534.3316) 
(list 5119.4375 535.0816) 
(list 5119.4375 534.0816) 
(list 5119.4375 534.0816) 
(list 5119.7375 524.0816)))
(apply 'command (append '("pline") coords '("c")))
(setq currobj (ssadd (entlast) currobj))
(command "_layer" "set" "prebias" "")
(setq coords (list 
(list 5119.4375 524.0816) 
(list 5119.4375 535.0816) 
(list 5045.415 534.3316) 
(list 5045.415 539.2746) 
(list 5119.4375 538.5246) 
(list 5119.4375 549.5246) 
(list 5120.5625 549.5246) 
(list 5120.5625 538.5246) 
(list 5194.585 539.2746) 
(list 5194.585 534.3316) 
(list 5120.5625 535.0816) 
(list 5120.5625 524.0816)))
(apply 'command (append '("pline") coords '("c")))
(setq currobj (ssadd (entlast) currobj))
(command "_layer" "set" "nitride" "")
(command "_layer" "set" "fda1" "")
(setq coords (list 
(list 5120.5625 535.2246) 
(list 5194.585 534.4746) 
(list 5194.585 534.6516) 
(list 5120.5625 535.3016)))
(apply 'command (append '("pline") coords '("c")))
(setq currobj (ssadd (entlast) currobj))
(setq coords (list 
(list 5120.5625 535.4446) 
(list 5194.585 534.7946) 
(list 5194.585 534.9716) 
(list 5120.5625 535.5216)))
(apply 'command (append '("pline") coords '("c")))
(setq currobj (ssadd (entlast) currobj))
(setq coords (list 
(list 5120.5625 535.6646) 
(list 5194.585 535.1146) 
(list 5194.585 535.2916) 
(list 5120.5625 535.7416)))
(apply 'command (append '("pline") coords '("c")))
(setq currobj (ssadd (entlast) currobj))
(setq coords (list 
(list 5120.5625 535.8846) 
(list 5194.585 535.4346) 
(list 5194.585 535.6116) 
(list 5120.5625 535.9616)))
(apply 'command (append '("pline") coords '("c")))
(setq currobj (ssadd (entlast) currobj))
(setq coords (list 
(list 5120.5625 536.1046) 
(list 5194.585 535.7546) 
(list 5194.585 535.9316) 
(list 5120.5625 536.1816)))
(apply 'command (append '("pline") coords '("c")))
(setq currobj (ssadd (entlast) currobj))
(setq coords (list 
(list 5120.5625 536.3246) 
(list 5194.585 536.0746) 
(list 5194.585 536.2516) 
(list 5120.5625 536.4016)))
(apply 'command (append '("pline") coords '("c")))
(setq currobj (ssadd (entlast) currobj))
(setq coords (list 
(list 5120.5625 536.5446) 
(list 5194.585 536.3946) 
(list 5194.585 536.5716) 
(list 5120.5625 536.6216)))
(apply 'command (append '("pline") coords '("c")))
(setq currobj (ssadd (entlast) currobj))
(setq coords (list 
(list 5120.5625 536.7646) 
(list 5194.585 536.7146) 
(list 5194.585 536.8916) 
(list 5120.5625 536.8416)))
(apply 'command (append '("pline") coords '("c")))
(setq currobj (ssadd (entlast) currobj))
(setq coords (list 
(list 5120.5625 536.9846) 
(list 5194.585 537.0346) 
(list 5194.585 537.2116) 
(list 5120.5625 537.0616)))
(apply 'command (append '("pline") coords '("c")))
(setq currobj (ssadd (entlast) currobj))
(setq coords (list 
(list 5120.5625 537.2046) 
(list 5194.585 537.3546) 
(list 5194.585 537.5316) 
(list 5120.5625 537.2816)))
(apply 'command (append '("pline") coords '("c")))
(setq currobj (ssadd (entlast) currobj))
(setq coords (list 
(list 5120.5625 537.4246) 
(list 5194.585 537.6746) 
(list 5194.585 537.8516) 
(list 5120.5625 537.5016)))
(apply 'command (append '("pline") coords '("c")))
(setq currobj (ssadd (entlast) currobj))
(setq coords (list 
(list 5120.5625 537.6446) 
(list 5194.585 537.9946) 
(list 5194.585 538.1716) 
(list 5120.5625 537.7216)))
(apply 'command (append '("pline") coords '("c")))
(setq currobj (ssadd (entlast) currobj))
(setq coords (list 
(list 5120.5625 537.8646) 
(list 5194.585 538.3146) 
(list 5194.585 538.4916) 
(list 5120.5625 537.9416)))
(apply 'command (append '("pline") coords '("c")))
(setq currobj (ssadd (entlast) currobj))
(setq coords (list 
(list 5120.5625 538.0846) 
(list 5194.585 538.6346) 
(list 5194.585 538.8116) 
(list 5120.5625 538.1616)))
(apply 'command (append '("pline") coords '("c")))
(setq currobj (ssadd (entlast) currobj))
(setq coords (list 
(list 5120.5625 538.3046) 
(list 5194.585 538.9546) 
(list 5194.585 539.1316) 
(list 5120.5625 538.3816)))
(apply 'command (append '("pline") coords '("c")))
(setq currobj (ssadd (entlast) currobj))
(setq coords (list 
(list 5119.4375 538.3816) 
(list 5045.415 539.1316) 
(list 5045.415 538.9546) 
(list 5119.4375 538.3046)))
(apply 'command (append '("pline") coords '("c")))
(setq currobj (ssadd (entlast) currobj))
(setq coords (list 
(list 5119.4375 538.1616) 
(list 5045.415 538.8116) 
(list 5045.415 538.6346) 
(list 5119.4375 538.0846)))
(apply 'command (append '("pline") coords '("c")))
(setq currobj (ssadd (entlast) currobj))
(setq coords (list 
(list 5119.4375 537.9416) 
(list 5045.415 538.4916) 
(list 5045.415 538.3146) 
(list 5119.4375 537.8646)))
(apply 'command (append '("pline") coords '("c")))
(setq currobj (ssadd (entlast) currobj))
(setq coords (list 
(list 5119.4375 537.7216) 
(list 5045.415 538.1716) 
(list 5045.415 537.9946) 
(list 5119.4375 537.6446)))
(apply 'command (append '("pline") coords '("c")))
(setq currobj (ssadd (entlast) currobj))
(setq coords (list 
(list 5119.4375 537.5016) 
(list 5045.415 537.8516) 
(list 5045.415 537.6746) 
(list 5119.4375 537.4246)))
(apply 'command (append '("pline") coords '("c")))
(setq currobj (ssadd (entlast) currobj))
(setq coords (list 
(list 5119.4375 537.2816) 
(list 5045.415 537.5316) 
(list 5045.415 537.3546) 
(list 5119.4375 537.2046)))
(apply 'command (append '("pline") coords '("c")))
(setq currobj (ssadd (entlast) currobj))
(setq coords (list 
(list 5119.4375 537.0616) 
(list 5045.415 537.2116) 
(list 5045.415 537.0346) 
(list 5119.4375 536.9846)))
(apply 'command (append '("pline") coords '("c")))
(setq currobj (ssadd (entlast) currobj))
(setq coords (list 
(list 5119.4375 536.8416) 
(list 5045.415 536.8916) 
(list 5045.415 536.7146) 
(list 5119.4375 536.7646)))
(apply 'command (append '("pline") coords '("c")))
(setq currobj (ssadd (entlast) currobj))
(setq coords (list 
(list 5119.4375 536.6216) 
(list 5045.415 536.5716) 
(list 5045.415 536.3946) 
(list 5119.4375 536.5446)))
(apply 'command (append '("pline") coords '("c")))
(setq currobj (ssadd (entlast) currobj))
(setq coords (list 
(list 5119.4375 536.4016) 
(list 5045.415 536.2516) 
(list 5045.415 536.0746) 
(list 5119.4375 536.3246)))
(apply 'command (append '("pline") coords '("c")))
(setq currobj (ssadd (entlast) currobj))
(setq coords (list 
(list 5119.4375 536.1816) 
(list 5045.415 535.9316) 
(list 5045.415 535.7546) 
(list 5119.4375 536.1046)))
(apply 'command (append '("pline") coords '("c")))
(setq currobj (ssadd (entlast) currobj))
(setq coords (list 
(list 5119.4375 535.9616) 
(list 5045.415 535.6116) 
(list 5045.415 535.4346) 
(list 5119.4375 535.8846)))
(apply 'command (append '("pline") coords '("c")))
(setq currobj (ssadd (entlast) currobj))
(setq coords (list 
(list 5119.4375 535.7416) 
(list 5045.415 535.2916) 
(list 5045.415 535.1146) 
(list 5119.4375 535.6646)))
(apply 'command (append '("pline") coords '("c")))
(setq currobj (ssadd (entlast) currobj))
(setq coords (list 
(list 5119.4375 535.5216) 
(list 5045.415 534.9716) 
(list 5045.415 534.7946) 
(list 5119.4375 535.4446)))
(apply 'command (append '("pline") coords '("c")))
(setq currobj (ssadd (entlast) currobj))
(setq coords (list 
(list 5119.4375 535.3016) 
(list 5045.415 534.6516) 
(list 5045.415 534.4746) 
(list 5119.4375 535.2246)))
(apply 'command (append '("pline") coords '("c")))
(setq currobj (ssadd (entlast) currobj))
(command "_layer" "set" "nitride" "")
(command "_layer" "set" "text" "")
(command "_circle" "5119.0625,524.0816" "0.075")
(command "_circle" "5119.0625,524.3816" "0.075")
(command "_circle" "5119.0625,524.6816" "0.075")
(command "_circle" "5119.0625,524.9816" "0.075")
(command "_circle" "5119.0625,525.2816" "0.075")
(command "_circle" "5118.7625,524.0816" "0.075")
(command "_circle" "5118.7625,524.3816" "0.075")
(command "_circle" "5118.7625,524.6816" "0.075")
(command "_circle" "5118.7625,524.9816" "0.075")
(command "_circle" "5118.7625,525.2816" "0.075")
(command "_circle" "5118.4625,524.0816" "0.075")
(command "_circle" "5118.4625,524.3816" "0.075")
(command "_circle" "5118.4625,524.6816" "0.075")
(command "_circle" "5118.4625,524.9816" "0.075")
(command "_circle" "5118.4625,525.2816" "0.075")
(command "_circle" "5118.1625,524.0816" "0.075")
(command "_circle" "5118.1625,524.3816" "0.075")
(command "_circle" "5118.1625,524.6816" "0.075")
(command "_circle" "5118.1625,524.9816" "0.075")
(command "_circle" "5118.1625,525.2816" "0.075")
(command "_circle" "5117.8625,524.0816" "0.075")
(command "_circle" "5117.8625,524.3816" "0.075")
(command "_circle" "5117.8625,524.6816" "0.075")
(command "_circle" "5117.8625,524.9816" "0.075")
(command "_circle" "5117.8625,525.2816" "0.075")
(command "_layer" "set" "nitride" "")
(setq coords (list 
(list 5120.2625 549.5246) 
(list 5120.2625 665.1693) 
(list 5119.7375 665.1693) 
(list 5119.7375 549.5246)))
(apply 'command (append '("pline") coords '("c")))
(setq currobj (ssadd (entlast) currobj))
(command "_layer" "set" "prebias" "")
(command "_rectangle" "5119.7375,549.5246" "5120.2625,665.1693")
(setq currobj (ssadd (entlast) currobj))
(command "_layer" "set" "nitride" "")
(setq coords (list 
(list 5120.2625 665.1693) 
(list 5120.5625 675.1693) 
(list 5120.5625 675.1693) 
(list 5120.5625 676.1693) 
(list 5194.585 675.4193) 
(list 5194.585 680.3623) 
(list 5120.5625 679.6123) 
(list 5120.5625 680.6123) 
(list 5120.5625 680.6123) 
(list 5120.2625 690.6123) 
(list 5119.7375 690.6123) 
(list 5119.4375 680.6123) 
(list 5119.4375 680.6123) 
(list 5119.4375 679.6123) 
(list 5045.415 680.3623) 
(list 5045.415 675.4193) 
(list 5119.4375 676.1693) 
(list 5119.4375 675.1693) 
(list 5119.4375 675.1693) 
(list 5119.7375 665.1693)))
(apply 'command (append '("pline") coords '("c")))
(setq currobj (ssadd (entlast) currobj))
(command "_layer" "set" "prebias" "")
(setq coords (list 
(list 5119.4375 665.1693) 
(list 5119.4375 676.1693) 
(list 5045.415 675.4193) 
(list 5045.415 680.3623) 
(list 5119.4375 679.6123) 
(list 5119.4375 690.6123) 
(list 5120.5625 690.6123) 
(list 5120.5625 679.6123) 
(list 5194.585 680.3623) 
(list 5194.585 675.4193) 
(list 5120.5625 676.1693) 
(list 5120.5625 665.1693)))
(apply 'command (append '("pline") coords '("c")))
(setq currobj (ssadd (entlast) currobj))
(command "_layer" "set" "nitride" "")
(command "_layer" "set" "fda1" "")
(setq coords (list 
(list 5120.5625 676.3123) 
(list 5194.585 675.5623) 
(list 5194.585 675.7393) 
(list 5120.5625 676.3893)))
(apply 'command (append '("pline") coords '("c")))
(setq currobj (ssadd (entlast) currobj))
(setq coords (list 
(list 5120.5625 676.5323) 
(list 5194.585 675.8823) 
(list 5194.585 676.0593) 
(list 5120.5625 676.6093)))
(apply 'command (append '("pline") coords '("c")))
(setq currobj (ssadd (entlast) currobj))
(setq coords (list 
(list 5120.5625 676.7523) 
(list 5194.585 676.2023) 
(list 5194.585 676.3793) 
(list 5120.5625 676.8293)))
(apply 'command (append '("pline") coords '("c")))
(setq currobj (ssadd (entlast) currobj))
(setq coords (list 
(list 5120.5625 676.9723) 
(list 5194.585 676.5223) 
(list 5194.585 676.6993) 
(list 5120.5625 677.0493)))
(apply 'command (append '("pline") coords '("c")))
(setq currobj (ssadd (entlast) currobj))
(setq coords (list 
(list 5120.5625 677.1923) 
(list 5194.585 676.8423) 
(list 5194.585 677.0193) 
(list 5120.5625 677.2693)))
(apply 'command (append '("pline") coords '("c")))
(setq currobj (ssadd (entlast) currobj))
(setq coords (list 
(list 5120.5625 677.4123) 
(list 5194.585 677.1623) 
(list 5194.585 677.3393) 
(list 5120.5625 677.4893)))
(apply 'command (append '("pline") coords '("c")))
(setq currobj (ssadd (entlast) currobj))
(setq coords (list 
(list 5120.5625 677.6323) 
(list 5194.585 677.4823) 
(list 5194.585 677.6593) 
(list 5120.5625 677.7093)))
(apply 'command (append '("pline") coords '("c")))
(setq currobj (ssadd (entlast) currobj))
(setq coords (list 
(list 5120.5625 677.8523) 
(list 5194.585 677.8023) 
(list 5194.585 677.9793) 
(list 5120.5625 677.9293)))
(apply 'command (append '("pline") coords '("c")))
(setq currobj (ssadd (entlast) currobj))
(setq coords (list 
(list 5120.5625 678.0723) 
(list 5194.585 678.1223) 
(list 5194.585 678.2993) 
(list 5120.5625 678.1493)))
(apply 'command (append '("pline") coords '("c")))
(setq currobj (ssadd (entlast) currobj))
(setq coords (list 
(list 5120.5625 678.2923) 
(list 5194.585 678.4423) 
(list 5194.585 678.6193) 
(list 5120.5625 678.3693)))
(apply 'command (append '("pline") coords '("c")))
(setq currobj (ssadd (entlast) currobj))
(setq coords (list 
(list 5120.5625 678.5123) 
(list 5194.585 678.7623) 
(list 5194.585 678.9393) 
(list 5120.5625 678.5893)))
(apply 'command (append '("pline") coords '("c")))
(setq currobj (ssadd (entlast) currobj))
(setq coords (list 
(list 5120.5625 678.7323) 
(list 5194.585 679.0823) 
(list 5194.585 679.2593) 
(list 5120.5625 678.8093)))
(apply 'command (append '("pline") coords '("c")))
(setq currobj (ssadd (entlast) currobj))
(setq coords (list 
(list 5120.5625 678.9523) 
(list 5194.585 679.4023) 
(list 5194.585 679.5793) 
(list 5120.5625 679.0293)))
(apply 'command (append '("pline") coords '("c")))
(setq currobj (ssadd (entlast) currobj))
(setq coords (list 
(list 5120.5625 679.1723) 
(list 5194.585 679.7223) 
(list 5194.585 679.8993) 
(list 5120.5625 679.2493)))
(apply 'command (append '("pline") coords '("c")))
(setq currobj (ssadd (entlast) currobj))
(setq coords (list 
(list 5120.5625 679.3923) 
(list 5194.585 680.0423) 
(list 5194.585 680.2193) 
(list 5120.5625 679.4693)))
(apply 'command (append '("pline") coords '("c")))
(setq currobj (ssadd (entlast) currobj))
(setq coords (list 
(list 5119.4375 679.4693) 
(list 5045.415 680.2193) 
(list 5045.415 680.0423) 
(list 5119.4375 679.3923)))
(apply 'command (append '("pline") coords '("c")))
(setq currobj (ssadd (entlast) currobj))
(setq coords (list 
(list 5119.4375 679.2493) 
(list 5045.415 679.8993) 
(list 5045.415 679.7223) 
(list 5119.4375 679.1723)))
(apply 'command (append '("pline") coords '("c")))
(setq currobj (ssadd (entlast) currobj))
(setq coords (list 
(list 5119.4375 679.0293) 
(list 5045.415 679.5793) 
(list 5045.415 679.4023) 
(list 5119.4375 678.9523)))
(apply 'command (append '("pline") coords '("c")))
(setq currobj (ssadd (entlast) currobj))
(setq coords (list 
(list 5119.4375 678.8093) 
(list 5045.415 679.2593) 
(list 5045.415 679.0823) 
(list 5119.4375 678.7323)))
(apply 'command (append '("pline") coords '("c")))
(setq currobj (ssadd (entlast) currobj))
(setq coords (list 
(list 5119.4375 678.5893) 
(list 5045.415 678.9393) 
(list 5045.415 678.7623) 
(list 5119.4375 678.5123)))
(apply 'command (append '("pline") coords '("c")))
(setq currobj (ssadd (entlast) currobj))
(setq coords (list 
(list 5119.4375 678.3693) 
(list 5045.415 678.6193) 
(list 5045.415 678.4423) 
(list 5119.4375 678.2923)))
(apply 'command (append '("pline") coords '("c")))
(setq currobj (ssadd (entlast) currobj))
(setq coords (list 
(list 5119.4375 678.1493) 
(list 5045.415 678.2993) 
(list 5045.415 678.1223) 
(list 5119.4375 678.0723)))
(apply 'command (append '("pline") coords '("c")))
(setq currobj (ssadd (entlast) currobj))
(setq coords (list 
(list 5119.4375 677.9293) 
(list 5045.415 677.9793) 
(list 5045.415 677.8023) 
(list 5119.4375 677.8523)))
(apply 'command (append '("pline") coords '("c")))
(setq currobj (ssadd (entlast) currobj))
(setq coords (list 
(list 5119.4375 677.7093) 
(list 5045.415 677.6593) 
(list 5045.415 677.4823) 
(list 5119.4375 677.6323)))
(apply 'command (append '("pline") coords '("c")))
(setq currobj (ssadd (entlast) currobj))
(setq coords (list 
(list 5119.4375 677.4893) 
(list 5045.415 677.3393) 
(list 5045.415 677.1623) 
(list 5119.4375 677.4123)))
(apply 'command (append '("pline") coords '("c")))
(setq currobj (ssadd (entlast) currobj))
(setq coords (list 
(list 5119.4375 677.2693) 
(list 5045.415 677.0193) 
(list 5045.415 676.8423) 
(list 5119.4375 677.1923)))
(apply 'command (append '("pline") coords '("c")))
(setq currobj (ssadd (entlast) currobj))
(setq coords (list 
(list 5119.4375 677.0493) 
(list 5045.415 676.6993) 
(list 5045.415 676.5223) 
(list 5119.4375 676.9723)))
(apply 'command (append '("pline") coords '("c")))
(setq currobj (ssadd (entlast) currobj))
(setq coords (list 
(list 5119.4375 676.8293) 
(list 5045.415 676.3793) 
(list 5045.415 676.2023) 
(list 5119.4375 676.7523)))
(apply 'command (append '("pline") coords '("c")))
(setq currobj (ssadd (entlast) currobj))
(setq coords (list 
(list 5119.4375 676.6093) 
(list 5045.415 676.0593) 
(list 5045.415 675.8823) 
(list 5119.4375 676.5323)))
(apply 'command (append '("pline") coords '("c")))
(setq currobj (ssadd (entlast) currobj))
(setq coords (list 
(list 5119.4375 676.3893) 
(list 5045.415 675.7393) 
(list 5045.415 675.5623) 
(list 5119.4375 676.3123)))
(apply 'command (append '("pline") coords '("c")))
(setq currobj (ssadd (entlast) currobj))
(command "_layer" "set" "nitride" "")
(command "_layer" "set" "text" "")
(command "_circle" "5119.0625,665.1693" "0.075")
(command "_circle" "5119.0625,665.4693" "0.075")
(command "_circle" "5119.0625,665.7693" "0.075")
(command "_circle" "5119.0625,666.0693" "0.075")
(command "_circle" "5119.0625,666.3693" "0.075")
(command "_circle" "5118.7625,665.1693" "0.075")
(command "_circle" "5118.7625,665.4693" "0.075")
(command "_circle" "5118.7625,665.7693" "0.075")
(command "_circle" "5118.7625,666.0693" "0.075")
(command "_circle" "5118.7625,666.3693" "0.075")
(command "_circle" "5118.4625,665.1693" "0.075")
(command "_circle" "5118.4625,665.4693" "0.075")
(command "_circle" "5118.4625,665.7693" "0.075")
(command "_circle" "5118.4625,666.0693" "0.075")
(command "_circle" "5118.4625,666.3693" "0.075")
(command "_circle" "5118.1625,665.1693" "0.075")
(command "_circle" "5118.1625,665.4693" "0.075")
(command "_circle" "5118.1625,665.7693" "0.075")
(command "_circle" "5118.1625,666.0693" "0.075")
(command "_circle" "5118.1625,666.3693" "0.075")
(command "_circle" "5117.8625,665.1693" "0.075")
(command "_circle" "5117.8625,665.4693" "0.075")
(command "_circle" "5117.8625,665.7693" "0.075")
(command "_circle" "5117.8625,666.0693" "0.075")
(command "_circle" "5117.8625,666.3693" "0.075")
(command "_layer" "set" "nitride" "")
(setq coords (list 
(list 5120.2625 690.6123) 
(list 5120.2625 806.257) 
(list 5119.7375 806.257) 
(list 5119.7375 690.6123)))
(apply 'command (append '("pline") coords '("c")))
(setq currobj (ssadd (entlast) currobj))
(command "_layer" "set" "prebias" "")
(command "_rectangle" "5119.7375,690.6123" "5120.2625,806.257")
(setq currobj (ssadd (entlast) currobj))
(command "_layer" "set" "nitride" "")
(setq coords (list 
(list 5120.2625 806.257) 
(list 5120.5625 816.257) 
(list 5120.5625 816.257) 
(list 5120.5625 817.257) 
(list 5194.585 816.507) 
(list 5194.585 821.45) 
(list 5120.5625 820.7) 
(list 5120.5625 821.7) 
(list 5120.5625 821.7) 
(list 5120.2625 831.7) 
(list 5119.7375 831.7) 
(list 5119.4375 821.7) 
(list 5119.4375 821.7) 
(list 5119.4375 820.7) 
(list 5045.415 821.45) 
(list 5045.415 816.507) 
(list 5119.4375 817.257) 
(list 5119.4375 816.257) 
(list 5119.4375 816.257) 
(list 5119.7375 806.257)))
(apply 'command (append '("pline") coords '("c")))
(setq currobj (ssadd (entlast) currobj))
(command "_layer" "set" "prebias" "")
(setq coords (list 
(list 5119.4375 806.257) 
(list 5119.4375 817.257) 
(list 5045.415 816.507) 
(list 5045.415 821.45) 
(list 5119.4375 820.7) 
(list 5119.4375 831.7) 
(list 5120.5625 831.7) 
(list 5120.5625 820.7) 
(list 5194.585 821.45) 
(list 5194.585 816.507) 
(list 5120.5625 817.257) 
(list 5120.5625 806.257)))
(apply 'command (append '("pline") coords '("c")))
(setq currobj (ssadd (entlast) currobj))
(command "_layer" "set" "nitride" "")
(command "_layer" "set" "fda1" "")
(setq coords (list 
(list 5120.5625 817.4) 
(list 5194.585 816.65) 
(list 5194.585 816.827) 
(list 5120.5625 817.477)))
(apply 'command (append '("pline") coords '("c")))
(setq currobj (ssadd (entlast) currobj))
(setq coords (list 
(list 5120.5625 817.62) 
(list 5194.585 816.97) 
(list 5194.585 817.147) 
(list 5120.5625 817.697)))
(apply 'command (append '("pline") coords '("c")))
(setq currobj (ssadd (entlast) currobj))
(setq coords (list 
(list 5120.5625 817.84) 
(list 5194.585 817.29) 
(list 5194.585 817.467) 
(list 5120.5625 817.917)))
(apply 'command (append '("pline") coords '("c")))
(setq currobj (ssadd (entlast) currobj))
(setq coords (list 
(list 5120.5625 818.06) 
(list 5194.585 817.61) 
(list 5194.585 817.787) 
(list 5120.5625 818.137)))
(apply 'command (append '("pline") coords '("c")))
(setq currobj (ssadd (entlast) currobj))
(setq coords (list 
(list 5120.5625 818.28) 
(list 5194.585 817.93) 
(list 5194.585 818.107) 
(list 5120.5625 818.357)))
(apply 'command (append '("pline") coords '("c")))
(setq currobj (ssadd (entlast) currobj))
(setq coords (list 
(list 5120.5625 818.5) 
(list 5194.585 818.25) 
(list 5194.585 818.427) 
(list 5120.5625 818.577)))
(apply 'command (append '("pline") coords '("c")))
(setq currobj (ssadd (entlast) currobj))
(setq coords (list 
(list 5120.5625 818.72) 
(list 5194.585 818.57) 
(list 5194.585 818.747) 
(list 5120.5625 818.797)))
(apply 'command (append '("pline") coords '("c")))
(setq currobj (ssadd (entlast) currobj))
(setq coords (list 
(list 5120.5625 818.94) 
(list 5194.585 818.89) 
(list 5194.585 819.067) 
(list 5120.5625 819.017)))
(apply 'command (append '("pline") coords '("c")))
(setq currobj (ssadd (entlast) currobj))
(setq coords (list 
(list 5120.5625 819.16) 
(list 5194.585 819.21) 
(list 5194.585 819.387) 
(list 5120.5625 819.237)))
(apply 'command (append '("pline") coords '("c")))
(setq currobj (ssadd (entlast) currobj))
(setq coords (list 
(list 5120.5625 819.38) 
(list 5194.585 819.53) 
(list 5194.585 819.707) 
(list 5120.5625 819.457)))
(apply 'command (append '("pline") coords '("c")))
(setq currobj (ssadd (entlast) currobj))
(setq coords (list 
(list 5120.5625 819.6) 
(list 5194.585 819.85) 
(list 5194.585 820.027) 
(list 5120.5625 819.677)))
(apply 'command (append '("pline") coords '("c")))
(setq currobj (ssadd (entlast) currobj))
(setq coords (list 
(list 5120.5625 819.82) 
(list 5194.585 820.17) 
(list 5194.585 820.347) 
(list 5120.5625 819.897)))
(apply 'command (append '("pline") coords '("c")))
(setq currobj (ssadd (entlast) currobj))
(setq coords (list 
(list 5120.5625 820.04) 
(list 5194.585 820.49) 
(list 5194.585 820.667) 
(list 5120.5625 820.117)))
(apply 'command (append '("pline") coords '("c")))
(setq currobj (ssadd (entlast) currobj))
(setq coords (list 
(list 5120.5625 820.26) 
(list 5194.585 820.81) 
(list 5194.585 820.987) 
(list 5120.5625 820.337)))
(apply 'command (append '("pline") coords '("c")))
(setq currobj (ssadd (entlast) currobj))
(setq coords (list 
(list 5120.5625 820.48) 
(list 5194.585 821.13) 
(list 5194.585 821.307) 
(list 5120.5625 820.557)))
(apply 'command (append '("pline") coords '("c")))
(setq currobj (ssadd (entlast) currobj))
(setq coords (list 
(list 5119.4375 820.557) 
(list 5045.415 821.307) 
(list 5045.415 821.13) 
(list 5119.4375 820.48)))
(apply 'command (append '("pline") coords '("c")))
(setq currobj (ssadd (entlast) currobj))
(setq coords (list 
(list 5119.4375 820.337) 
(list 5045.415 820.987) 
(list 5045.415 820.81) 
(list 5119.4375 820.26)))
(apply 'command (append '("pline") coords '("c")))
(setq currobj (ssadd (entlast) currobj))
(setq coords (list 
(list 5119.4375 820.117) 
(list 5045.415 820.667) 
(list 5045.415 820.49) 
(list 5119.4375 820.04)))
(apply 'command (append '("pline") coords '("c")))
(setq currobj (ssadd (entlast) currobj))
(setq coords (list 
(list 5119.4375 819.897) 
(list 5045.415 820.347) 
(list 5045.415 820.17) 
(list 5119.4375 819.82)))
(apply 'command (append '("pline") coords '("c")))
(setq currobj (ssadd (entlast) currobj))
(setq coords (list 
(list 5119.4375 819.677) 
(list 5045.415 820.027) 
(list 5045.415 819.85) 
(list 5119.4375 819.6)))
(apply 'command (append '("pline") coords '("c")))
(setq currobj (ssadd (entlast) currobj))
(setq coords (list 
(list 5119.4375 819.457) 
(list 5045.415 819.707) 
(list 5045.415 819.53) 
(list 5119.4375 819.38)))
(apply 'command (append '("pline") coords '("c")))
(setq currobj (ssadd (entlast) currobj))
(setq coords (list 
(list 5119.4375 819.237) 
(list 5045.415 819.387) 
(list 5045.415 819.21) 
(list 5119.4375 819.16)))
(apply 'command (append '("pline") coords '("c")))
(setq currobj (ssadd (entlast) currobj))
(setq coords (list 
(list 5119.4375 819.017) 
(list 5045.415 819.067) 
(list 5045.415 818.89) 
(list 5119.4375 818.94)))
(apply 'command (append '("pline") coords '("c")))
(setq currobj (ssadd (entlast) currobj))
(setq coords (list 
(list 5119.4375 818.797) 
(list 5045.415 818.747) 
(list 5045.415 818.57) 
(list 5119.4375 818.72)))
(apply 'command (append '("pline") coords '("c")))
(setq currobj (ssadd (entlast) currobj))
(setq coords (list 
(list 5119.4375 818.577) 
(list 5045.415 818.427) 
(list 5045.415 818.25) 
(list 5119.4375 818.5)))
(apply 'command (append '("pline") coords '("c")))
(setq currobj (ssadd (entlast) currobj))
(setq coords (list 
(list 5119.4375 818.357) 
(list 5045.415 818.107) 
(list 5045.415 817.93) 
(list 5119.4375 818.28)))
(apply 'command (append '("pline") coords '("c")))
(setq currobj (ssadd (entlast) currobj))
(setq coords (list 
(list 5119.4375 818.137) 
(list 5045.415 817.787) 
(list 5045.415 817.61) 
(list 5119.4375 818.06)))
(apply 'command (append '("pline") coords '("c")))
(setq currobj (ssadd (entlast) currobj))
(setq coords (list 
(list 5119.4375 817.917) 
(list 5045.415 817.467) 
(list 5045.415 817.29) 
(list 5119.4375 817.84)))
(apply 'command (append '("pline") coords '("c")))
(setq currobj (ssadd (entlast) currobj))
(setq coords (list 
(list 5119.4375 817.697) 
(list 5045.415 817.147) 
(list 5045.415 816.97) 
(list 5119.4375 817.62)))
(apply 'command (append '("pline") coords '("c")))
(setq currobj (ssadd (entlast) currobj))
(setq coords (list 
(list 5119.4375 817.477) 
(list 5045.415 816.827) 
(list 5045.415 816.65) 
(list 5119.4375 817.4)))
(apply 'command (append '("pline") coords '("c")))
(setq currobj (ssadd (entlast) currobj))
(command "_layer" "set" "nitride" "")
(command "_layer" "set" "text" "")
(command "_circle" "5119.0625,806.257" "0.075")
(command "_circle" "5119.0625,806.557" "0.075")
(command "_circle" "5119.0625,806.857" "0.075")
(command "_circle" "5119.0625,807.157" "0.075")
(command "_circle" "5119.0625,807.457" "0.075")
(command "_circle" "5118.7625,806.257" "0.075")
(command "_circle" "5118.7625,806.557" "0.075")
(command "_circle" "5118.7625,806.857" "0.075")
(command "_circle" "5118.7625,807.157" "0.075")
(command "_circle" "5118.7625,807.457" "0.075")
(command "_circle" "5118.4625,806.257" "0.075")
(command "_circle" "5118.4625,806.557" "0.075")
(command "_circle" "5118.4625,806.857" "0.075")
(command "_circle" "5118.4625,807.157" "0.075")
(command "_circle" "5118.4625,807.457" "0.075")
(command "_circle" "5118.1625,806.257" "0.075")
(command "_circle" "5118.1625,806.557" "0.075")
(command "_circle" "5118.1625,806.857" "0.075")
(command "_circle" "5118.1625,807.157" "0.075")
(command "_circle" "5118.1625,807.457" "0.075")
(command "_circle" "5117.8625,806.257" "0.075")
(command "_circle" "5117.8625,806.557" "0.075")
(command "_circle" "5117.8625,806.857" "0.075")
(command "_circle" "5117.8625,807.157" "0.075")
(command "_circle" "5117.8625,807.457" "0.075")
(command "_layer" "set" "nitride" "")
(setq coords (list 
(list 5120.2625 831.7) 
(list 5120.2625 836.7) 
(list 5119.7375 836.7) 
(list 5119.7375 831.7)))
(apply 'command (append '("pline") coords '("c")))
(setq currobj (ssadd (entlast) currobj))
(command "_layer" "set" "prebias" "")
(command "_rectangle" "5119.7375,831.7" "5120.2625,836.7")
(setq currobj (ssadd (entlast) currobj))
(command "_layer" "set" "nitride" "")
(setq cooledsinglenanobeam16 currobj)
(setq currobj nil)
(setq currobj (ssadd))
; DRAWING PHOTONIC CRYSTAL
(command "_layer" "set" "negYjunc" "")
(setq coords (list 
(list 5120.125 866.7) 
(list 5120 851.7) 
(list 5120 866.7)))
(apply 'command (append '("pline") coords '("c")))
(setq currobj (ssadd (entlast) currobj))
(setq coords (list 
(list 5120.2625 836.7) 
(list 5120.405 866.7) 
(list 5121.142 866.7) 
(list 5121.142 836.7)))
(apply 'command (append '("pline") coords '("c")))
(setq currobj (ssadd (entlast) currobj))
(setq coords (list 
(list 5119.875 866.7) 
(list 5120 851.7) 
(list 5120 866.7)))
(apply 'command (append '("pline") coords '("c")))
(setq currobj (ssadd (entlast) currobj))
(setq coords (list 
(list 5119.7375 836.7) 
(list 5119.595 866.7) 
(list 5118.858 866.7) 
(list 5118.858 836.7)))
(apply 'command (append '("pline") coords '("c")))
(setq currobj (ssadd (entlast) currobj))
(command "_layer" "set" "nitride" "")
(setq yjunction16 currobj)
(setq currobj nil)
(setq currobj (ssadd))
(setq tap16 nil)
(setq tap16 (ssadd))
(command "_layer" "set" "phc" "")
(setq coords (list 
(list 5120 866.7) 
(list 5120.125 866.7) 
(list 5120.125 866.7103) 
(list 5120.125 866.7206) 
(list 5120.125 866.7308) 
(list 5120.125 866.7411) 
(list 5120.125 866.7514) 
(list 5120.125 866.7617) 
(list 5120.125 866.7719) 
(list 5120.125 866.7822) 
(list 5120.125 866.7925) 
(list 5120.125 866.8028) 
(list 5120.125 866.8131) 
(list 5120.125 866.8233) 
(list 5120.125 866.8336) 
(list 5120.125 866.8439) 
(list 5120.125 866.8542) 
(list 5120.125 866.8644) 
(list 5120.125 866.8747) 
(list 5120.125 866.885) 
(list 5120.125 866.8953) 
(list 5120.125 866.9056) 
(list 5120.125 866.9158) 
(list 5120.125 866.9261) 
(list 5120.125 866.9364) 
(list 5120.125 866.9467) 
(list 5120.125 866.9569) 
(list 5120.125 866.9672) 
(list 5120.125 866.9775) 
(list 5120.125 866.9878) 
(list 5120.125 866.9981) 
(list 5120.125 867.0083) 
(list 5120.125 867.0186) 
(list 5120.125 867.0289) 
(list 5120.125 867.0392) 
(list 5120.125 867.0494) 
(list 5120.125 867.0597) 
(list 5120.125 867.07) 
(list 5120 867.07)))
(apply 'command (append '("pline") coords '("c")))
(setq tap16 (ssadd (entlast) tap16))
(command "_mirror" (entlast) "" "5120,900" "5120,901" "No")
(setq tap16 (ssadd (entlast) tap16))
(setq coords (list 
(list 5120.4161 866.7) 
(list 5120.405 866.7) 
(list 5120.4053 866.7103) 
(list 5120.4056 866.7206) 
(list 5120.4058 866.7308) 
(list 5120.406 866.7411) 
(list 5120.4061 866.7514) 
(list 5120.4061 866.7617) 
(list 5120.4059 866.7719) 
(list 5120.4057 866.7822) 
(list 5120.4054 866.7925) 
(list 5120.405 866.8028) 
(list 5120.4045 866.8131) 
(list 5120.404 866.8233) 
(list 5120.4034 866.8336) 
(list 5120.4028 866.8439) 
(list 5120.4023 866.8542) 
(list 5120.4018 866.8644) 
(list 5120.4014 866.8747) 
(list 5120.4011 866.885) 
(list 5120.4009 866.8953) 
(list 5120.4009 866.9056) 
(list 5120.4012 866.9158) 
(list 5120.4015 866.9261) 
(list 5120.4021 866.9364) 
(list 5120.4029 866.9467) 
(list 5120.4039 866.9569) 
(list 5120.405 866.9672) 
(list 5120.4062 866.9775) 
(list 5120.4075 866.9878) 
(list 5120.4089 866.9981) 
(list 5120.4103 867.0083) 
(list 5120.4116 867.0186) 
(list 5120.4129 867.0289) 
(list 5120.414 867.0392) 
(list 5120.4149 867.0494) 
(list 5120.4156 867.0597) 
(list 5120.4161 867.07) 
(list 5120.4161 867.07)))
(apply 'command (append '("pline") coords '("c")))
(setq tap16 (ssadd (entlast) tap16))
(command "_mirror" (entlast) "" "5120,900" "5120,901" "No")
(setq tap16 (ssadd (entlast) tap16))
(setq coords (list 
(list 5121.142 866.7) 
(list 5120.4161 866.7) 
(list 5120.4161 866.7103) 
(list 5120.4161 866.7206) 
(list 5120.4161 866.7308) 
(list 5120.4161 866.7411) 
(list 5120.4161 866.7514) 
(list 5120.4161 866.7617) 
(list 5120.4161 866.7719) 
(list 5120.4161 866.7822) 
(list 5120.4161 866.7925) 
(list 5120.4161 866.8028) 
(list 5120.4161 866.8131) 
(list 5120.4161 866.8233) 
(list 5120.4161 866.8336) 
(list 5120.4161 866.8439) 
(list 5120.4161 866.8542) 
(list 5120.4161 866.8644) 
(list 5120.4161 866.8747) 
(list 5120.4161 866.885) 
(list 5120.4161 866.8953) 
(list 5120.4161 866.9056) 
(list 5120.4161 866.9158) 
(list 5120.4161 866.9261) 
(list 5120.4161 866.9364) 
(list 5120.4161 866.9467) 
(list 5120.4161 866.9569) 
(list 5120.4161 866.9672) 
(list 5120.4161 866.9775) 
(list 5120.4161 866.9878) 
(list 5120.4161 866.9981) 
(list 5120.4161 867.0083) 
(list 5120.4161 867.0186) 
(list 5120.4161 867.0289) 
(list 5120.4161 867.0392) 
(list 5120.4161 867.0494) 
(list 5120.4161 867.0597) 
(list 5120.4161 867.07) 
(list 5121.142 867.07)))
(apply 'command (append '("pline") coords '("c")))
(setq tap16 (ssadd (entlast) tap16))
(command "_mirror" (entlast) "" "5120,900" "5120,901" "No")
(setq tap16 (ssadd (entlast) tap16))
(setq coords (list 
(list 5120 867.07) 
(list 5120.125 867.07) 
(list 5120.125 867.0803) 
(list 5120.125 867.0906) 
(list 5120.125 867.1008) 
(list 5120.125 867.1111) 
(list 5120.125 867.1214) 
(list 5120.125 867.1317) 
(list 5120.125 867.1419) 
(list 5120.125 867.1522) 
(list 5120.125 867.1625) 
(list 5120.125 867.1728) 
(list 5120.125 867.1831) 
(list 5120.125 867.1933) 
(list 5120.125 867.2036) 
(list 5120.125 867.2139) 
(list 5120.125 867.2242) 
(list 5120.125 867.2344) 
(list 5120.125 867.2447) 
(list 5120.125 867.255) 
(list 5120.125 867.2653) 
(list 5120.125 867.2756) 
(list 5120.125 867.2858) 
(list 5120.125 867.2961) 
(list 5120.125 867.3064) 
(list 5120.125 867.3167) 
(list 5120.125 867.3269) 
(list 5120.125 867.3372) 
(list 5120.125 867.3475) 
(list 5120.125 867.3578) 
(list 5120.125 867.3681) 
(list 5120.125 867.3783) 
(list 5120.125 867.3886) 
(list 5120.125 867.3989) 
(list 5120.125 867.4092) 
(list 5120.125 867.4194) 
(list 5120.125 867.4297) 
(list 5120.125 867.44) 
(list 5120 867.44)))
(apply 'command (append '("pline") coords '("c")))
(setq tap16 (ssadd (entlast) tap16))
(command "_mirror" (entlast) "" "5120,900" "5120,901" "No")
(setq tap16 (ssadd (entlast) tap16))
(setq coords (list 
(list 5120.4271 867.07) 
(list 5120.4161 867.07) 
(list 5120.4162 867.0803) 
(list 5120.4161 867.0906) 
(list 5120.4156 867.1008) 
(list 5120.4148 867.1111) 
(list 5120.4138 867.1214) 
(list 5120.4124 867.1317) 
(list 5120.4108 867.1419) 
(list 5120.409 867.1522) 
(list 5120.407 867.1625) 
(list 5120.4049 867.1728) 
(list 5120.4029 867.1831) 
(list 5120.4008 867.1933) 
(list 5120.3989 867.2036) 
(list 5120.3971 867.2139) 
(list 5120.3957 867.2242) 
(list 5120.3945 867.2344) 
(list 5120.3936 867.2447) 
(list 5120.3932 867.255) 
(list 5120.3932 867.2653) 
(list 5120.3937 867.2756) 
(list 5120.3946 867.2858) 
(list 5120.3959 867.2961) 
(list 5120.3976 867.3064) 
(list 5120.3998 867.3167) 
(list 5120.4022 867.3269) 
(list 5120.4049 867.3372) 
(list 5120.4078 867.3475) 
(list 5120.4108 867.3578) 
(list 5120.4137 867.3681) 
(list 5120.4166 867.3783) 
(list 5120.4193 867.3886) 
(list 5120.4217 867.3989) 
(list 5120.4238 867.4092) 
(list 5120.4254 867.4194) 
(list 5120.4265 867.4297) 
(list 5120.4271 867.44) 
(list 5120.4271 867.44)))
(apply 'command (append '("pline") coords '("c")))
(setq tap16 (ssadd (entlast) tap16))
(command "_mirror" (entlast) "" "5120,900" "5120,901" "No")
(setq tap16 (ssadd (entlast) tap16))
(setq coords (list 
(list 5121.142 867.07) 
(list 5120.4271 867.07) 
(list 5120.4271 867.0803) 
(list 5120.4271 867.0906) 
(list 5120.4271 867.1008) 
(list 5120.4271 867.1111) 
(list 5120.4271 867.1214) 
(list 5120.4271 867.1317) 
(list 5120.4271 867.1419) 
(list 5120.4271 867.1522) 
(list 5120.4271 867.1625) 
(list 5120.4271 867.1728) 
(list 5120.4271 867.1831) 
(list 5120.4271 867.1933) 
(list 5120.4271 867.2036) 
(list 5120.4271 867.2139) 
(list 5120.4271 867.2242) 
(list 5120.4271 867.2344) 
(list 5120.4271 867.2447) 
(list 5120.4271 867.255) 
(list 5120.4271 867.2653) 
(list 5120.4271 867.2756) 
(list 5120.4271 867.2858) 
(list 5120.4271 867.2961) 
(list 5120.4271 867.3064) 
(list 5120.4271 867.3167) 
(list 5120.4271 867.3269) 
(list 5120.4271 867.3372) 
(list 5120.4271 867.3475) 
(list 5120.4271 867.3578) 
(list 5120.4271 867.3681) 
(list 5120.4271 867.3783) 
(list 5120.4271 867.3886) 
(list 5120.4271 867.3989) 
(list 5120.4271 867.4092) 
(list 5120.4271 867.4194) 
(list 5120.4271 867.4297) 
(list 5120.4271 867.44) 
(list 5121.142 867.44)))
(apply 'command (append '("pline") coords '("c")))
(setq tap16 (ssadd (entlast) tap16))
(command "_mirror" (entlast) "" "5120,900" "5120,901" "No")
(setq tap16 (ssadd (entlast) tap16))
(setq coords (list 
(list 5120 867.44) 
(list 5120.125 867.44) 
(list 5120.125 867.4503) 
(list 5120.125 867.4606) 
(list 5120.125 867.4708) 
(list 5120.125 867.4811) 
(list 5120.125 867.4914) 
(list 5120.125 867.5017) 
(list 5120.125 867.5119) 
(list 5120.125 867.5222) 
(list 5120.125 867.5325) 
(list 5120.125 867.5428) 
(list 5120.125 867.5531) 
(list 5120.125 867.5633) 
(list 5120.125 867.5736) 
(list 5120.125 867.5839) 
(list 5120.125 867.5942) 
(list 5120.125 867.6044) 
(list 5120.125 867.6147) 
(list 5120.125 867.625) 
(list 5120.125 867.6353) 
(list 5120.125 867.6456) 
(list 5120.125 867.6558) 
(list 5120.125 867.6661) 
(list 5120.125 867.6764) 
(list 5120.125 867.6867) 
(list 5120.125 867.6969) 
(list 5120.125 867.7072) 
(list 5120.125 867.7175) 
(list 5120.125 867.7278) 
(list 5120.125 867.7381) 
(list 5120.125 867.7483) 
(list 5120.125 867.7586) 
(list 5120.125 867.7689) 
(list 5120.125 867.7792) 
(list 5120.125 867.7894) 
(list 5120.125 867.7997) 
(list 5120.125 867.81) 
(list 5120 867.81)))
(apply 'command (append '("pline") coords '("c")))
(setq tap16 (ssadd (entlast) tap16))
(command "_mirror" (entlast) "" "5120,900" "5120,901" "No")
(setq tap16 (ssadd (entlast) tap16))
(setq coords (list 
(list 5120.4382 867.44) 
(list 5120.4271 867.44) 
(list 5120.4271 867.4503) 
(list 5120.4266 867.4606) 
(list 5120.4254 867.4708) 
(list 5120.4237 867.4811) 
(list 5120.4214 867.4914) 
(list 5120.4187 867.5017) 
(list 5120.4156 867.5119) 
(list 5120.4122 867.5222) 
(list 5120.4086 867.5325) 
(list 5120.4049 867.5428) 
(list 5120.4012 867.5531) 
(list 5120.3977 867.5633) 
(list 5120.3944 867.5736) 
(list 5120.3915 867.5839) 
(list 5120.3891 867.5942) 
(list 5120.3872 867.6044) 
(list 5120.3859 867.6147) 
(list 5120.3853 867.625) 
(list 5120.3855 867.6353) 
(list 5120.3864 867.6456) 
(list 5120.388 867.6558) 
(list 5120.3902 867.6661) 
(list 5120.3932 867.6764) 
(list 5120.3966 867.6867) 
(list 5120.4006 867.6969) 
(list 5120.4049 867.7072) 
(list 5120.4094 867.7175) 
(list 5120.414 867.7278) 
(list 5120.4186 867.7381) 
(list 5120.4229 867.7483) 
(list 5120.427 867.7586) 
(list 5120.4306 867.7689) 
(list 5120.4336 867.7792) 
(list 5120.4359 867.7894) 
(list 5120.4375 867.7997) 
(list 5120.4382 867.81) 
(list 5120.4382 867.81)))
(apply 'command (append '("pline") coords '("c")))
(setq tap16 (ssadd (entlast) tap16))
(command "_mirror" (entlast) "" "5120,900" "5120,901" "No")
(setq tap16 (ssadd (entlast) tap16))
(setq coords (list 
(list 5121.142 867.44) 
(list 5120.4382 867.44) 
(list 5120.4382 867.4503) 
(list 5120.4382 867.4606) 
(list 5120.4382 867.4708) 
(list 5120.4382 867.4811) 
(list 5120.4382 867.4914) 
(list 5120.4382 867.5017) 
(list 5120.4382 867.5119) 
(list 5120.4382 867.5222) 
(list 5120.4382 867.5325) 
(list 5120.4382 867.5428) 
(list 5120.4382 867.5531) 
(list 5120.4382 867.5633) 
(list 5120.4382 867.5736) 
(list 5120.4382 867.5839) 
(list 5120.4382 867.5942) 
(list 5120.4382 867.6044) 
(list 5120.4382 867.6147) 
(list 5120.4382 867.625) 
(list 5120.4382 867.6353) 
(list 5120.4382 867.6456) 
(list 5120.4382 867.6558) 
(list 5120.4382 867.6661) 
(list 5120.4382 867.6764) 
(list 5120.4382 867.6867) 
(list 5120.4382 867.6969) 
(list 5120.4382 867.7072) 
(list 5120.4382 867.7175) 
(list 5120.4382 867.7278) 
(list 5120.4382 867.7381) 
(list 5120.4382 867.7483) 
(list 5120.4382 867.7586) 
(list 5120.4382 867.7689) 
(list 5120.4382 867.7792) 
(list 5120.4382 867.7894) 
(list 5120.4382 867.7997) 
(list 5120.4382 867.81) 
(list 5121.142 867.81)))
(apply 'command (append '("pline") coords '("c")))
(setq tap16 (ssadd (entlast) tap16))
(command "_mirror" (entlast) "" "5120,900" "5120,901" "No")
(setq tap16 (ssadd (entlast) tap16))
(setq coords (list 
(list 5120 867.81) 
(list 5120.125 867.81) 
(list 5120.125 867.8203) 
(list 5120.125 867.8306) 
(list 5120.125 867.8408) 
(list 5120.125 867.8511) 
(list 5120.125 867.8614) 
(list 5120.125 867.8717) 
(list 5120.125 867.8819) 
(list 5120.125 867.8922) 
(list 5120.125 867.9025) 
(list 5120.125 867.9128) 
(list 5120.125 867.9231) 
(list 5120.125 867.9333) 
(list 5120.125 867.9436) 
(list 5120.125 867.9539) 
(list 5120.125 867.9642) 
(list 5120.125 867.9744) 
(list 5120.125 867.9847) 
(list 5120.125 867.995) 
(list 5120.125 868.0053) 
(list 5120.125 868.0156) 
(list 5120.125 868.0258) 
(list 5120.125 868.0361) 
(list 5120.125 868.0464) 
(list 5120.125 868.0567) 
(list 5120.125 868.0669) 
(list 5120.125 868.0772) 
(list 5120.125 868.0875) 
(list 5120.125 868.0978) 
(list 5120.125 868.1081) 
(list 5120.125 868.1183) 
(list 5120.125 868.1286) 
(list 5120.125 868.1389) 
(list 5120.125 868.1492) 
(list 5120.125 868.1594) 
(list 5120.125 868.1697) 
(list 5120.125 868.18) 
(list 5120 868.18)))
(apply 'command (append '("pline") coords '("c")))
(setq tap16 (ssadd (entlast) tap16))
(command "_mirror" (entlast) "" "5120,900" "5120,901" "No")
(setq tap16 (ssadd (entlast) tap16))
(setq coords (list 
(list 5120.4493 867.81) 
(list 5120.4382 867.81) 
(list 5120.4381 867.8203) 
(list 5120.4371 867.8306) 
(list 5120.4352 867.8408) 
(list 5120.4325 867.8511) 
(list 5120.4291 867.8614) 
(list 5120.4251 867.8717) 
(list 5120.4205 867.8819) 
(list 5120.4155 867.8922) 
(list 5120.4102 867.9025) 
(list 5120.4049 867.9128) 
(list 5120.3996 867.9231) 
(list 5120.3946 867.9333) 
(list 5120.3899 867.9436) 
(list 5120.3858 867.9539) 
(list 5120.3825 867.9642) 
(list 5120.3799 867.9744) 
(list 5120.3782 867.9847) 
(list 5120.3775 867.995) 
(list 5120.3778 868.0053) 
(list 5120.3791 868.0156) 
(list 5120.3814 868.0258) 
(list 5120.3846 868.0361) 
(list 5120.3887 868.0464) 
(list 5120.3935 868.0567) 
(list 5120.3989 868.0669) 
(list 5120.4048 868.0772) 
(list 5120.411 868.0875) 
(list 5120.4173 868.0978) 
(list 5120.4234 868.1081) 
(list 5120.4293 868.1183) 
(list 5120.4347 868.1286) 
(list 5120.4394 868.1389) 
(list 5120.4434 868.1492) 
(list 5120.4464 868.1594) 
(list 5120.4484 868.1697) 
(list 5120.4493 868.18) 
(list 5120.4493 868.18)))
(apply 'command (append '("pline") coords '("c")))
(setq tap16 (ssadd (entlast) tap16))
(command "_mirror" (entlast) "" "5120,900" "5120,901" "No")
(setq tap16 (ssadd (entlast) tap16))
(setq coords (list 
(list 5121.142 867.81) 
(list 5120.4493 867.81) 
(list 5120.4493 867.8203) 
(list 5120.4493 867.8306) 
(list 5120.4493 867.8408) 
(list 5120.4493 867.8511) 
(list 5120.4493 867.8614) 
(list 5120.4493 867.8717) 
(list 5120.4493 867.8819) 
(list 5120.4493 867.8922) 
(list 5120.4493 867.9025) 
(list 5120.4493 867.9128) 
(list 5120.4493 867.9231) 
(list 5120.4493 867.9333) 
(list 5120.4493 867.9436) 
(list 5120.4493 867.9539) 
(list 5120.4493 867.9642) 
(list 5120.4493 867.9744) 
(list 5120.4493 867.9847) 
(list 5120.4493 867.995) 
(list 5120.4493 868.0053) 
(list 5120.4493 868.0156) 
(list 5120.4493 868.0258) 
(list 5120.4493 868.0361) 
(list 5120.4493 868.0464) 
(list 5120.4493 868.0567) 
(list 5120.4493 868.0669) 
(list 5120.4493 868.0772) 
(list 5120.4493 868.0875) 
(list 5120.4493 868.0978) 
(list 5120.4493 868.1081) 
(list 5120.4493 868.1183) 
(list 5120.4493 868.1286) 
(list 5120.4493 868.1389) 
(list 5120.4493 868.1492) 
(list 5120.4493 868.1594) 
(list 5120.4493 868.1697) 
(list 5120.4493 868.18) 
(list 5121.142 868.18)))
(apply 'command (append '("pline") coords '("c")))
(setq tap16 (ssadd (entlast) tap16))
(command "_mirror" (entlast) "" "5120,900" "5120,901" "No")
(setq tap16 (ssadd (entlast) tap16))
(setq coords (list 
(list 5120 868.18) 
(list 5120.125 868.18) 
(list 5120.125 868.1903) 
(list 5120.125 868.2006) 
(list 5120.125 868.2108) 
(list 5120.125 868.2211) 
(list 5120.125 868.2314) 
(list 5120.125 868.2417) 
(list 5120.125 868.2519) 
(list 5120.125 868.2622) 
(list 5120.125 868.2725) 
(list 5120.125 868.2828) 
(list 5120.125 868.2931) 
(list 5120.125 868.3033) 
(list 5120.125 868.3136) 
(list 5120.125 868.3239) 
(list 5120.125 868.3342) 
(list 5120.125 868.3444) 
(list 5120.125 868.3547) 
(list 5120.125 868.365) 
(list 5120.125 868.3753) 
(list 5120.125 868.3856) 
(list 5120.125 868.3958) 
(list 5120.125 868.4061) 
(list 5120.125 868.4164) 
(list 5120.125 868.4267) 
(list 5120.125 868.4369) 
(list 5120.125 868.4472) 
(list 5120.125 868.4575) 
(list 5120.125 868.4678) 
(list 5120.125 868.4781) 
(list 5120.125 868.4883) 
(list 5120.125 868.4986) 
(list 5120.125 868.5089) 
(list 5120.125 868.5192) 
(list 5120.125 868.5294) 
(list 5120.125 868.5397) 
(list 5120.125 868.55) 
(list 5120 868.55)))
(apply 'command (append '("pline") coords '("c")))
(setq tap16 (ssadd (entlast) tap16))
(command "_mirror" (entlast) "" "5120,900" "5120,901" "No")
(setq tap16 (ssadd (entlast) tap16))
(setq coords (list 
(list 5120.4603 868.18) 
(list 5120.4493 868.18) 
(list 5120.449 868.1903) 
(list 5120.4476 868.2006) 
(list 5120.445 868.2108) 
(list 5120.4414 868.2211) 
(list 5120.4368 868.2314) 
(list 5120.4314 868.2417) 
(list 5120.4253 868.2519) 
(list 5120.4187 868.2622) 
(list 5120.4118 868.2725) 
(list 5120.4048 868.2828) 
(list 5120.3979 868.2931) 
(list 5120.3914 868.3033) 
(list 5120.3854 868.3136) 
(list 5120.3802 868.3239) 
(list 5120.3759 868.3342) 
(list 5120.3726 868.3444) 
(list 5120.3705 868.3547) 
(list 5120.3696 868.365) 
(list 5120.37 868.3753) 
(list 5120.3718 868.3856) 
(list 5120.3748 868.3958) 
(list 5120.3789 868.4061) 
(list 5120.3842 868.4164) 
(list 5120.3904 868.4267) 
(list 5120.3973 868.4369) 
(list 5120.4048 868.4472) 
(list 5120.4126 868.4575) 
(list 5120.4205 868.4678) 
(list 5120.4282 868.4781) 
(list 5120.4356 868.4883) 
(list 5120.4424 868.4986) 
(list 5120.4483 868.5089) 
(list 5120.4532 868.5192) 
(list 5120.4569 868.5294) 
(list 5120.4593 868.5397) 
(list 5120.4603 868.55) 
(list 5120.4603 868.55)))
(apply 'command (append '("pline") coords '("c")))
(setq tap16 (ssadd (entlast) tap16))
(command "_mirror" (entlast) "" "5120,900" "5120,901" "No")
(setq tap16 (ssadd (entlast) tap16))
(setq coords (list 
(list 5121.142 868.18) 
(list 5120.4603 868.18) 
(list 5120.4603 868.1903) 
(list 5120.4603 868.2006) 
(list 5120.4603 868.2108) 
(list 5120.4603 868.2211) 
(list 5120.4603 868.2314) 
(list 5120.4603 868.2417) 
(list 5120.4603 868.2519) 
(list 5120.4603 868.2622) 
(list 5120.4603 868.2725) 
(list 5120.4603 868.2828) 
(list 5120.4603 868.2931) 
(list 5120.4603 868.3033) 
(list 5120.4603 868.3136) 
(list 5120.4603 868.3239) 
(list 5120.4603 868.3342) 
(list 5120.4603 868.3444) 
(list 5120.4603 868.3547) 
(list 5120.4603 868.365) 
(list 5120.4603 868.3753) 
(list 5120.4603 868.3856) 
(list 5120.4603 868.3958) 
(list 5120.4603 868.4061) 
(list 5120.4603 868.4164) 
(list 5120.4603 868.4267) 
(list 5120.4603 868.4369) 
(list 5120.4603 868.4472) 
(list 5120.4603 868.4575) 
(list 5120.4603 868.4678) 
(list 5120.4603 868.4781) 
(list 5120.4603 868.4883) 
(list 5120.4603 868.4986) 
(list 5120.4603 868.5089) 
(list 5120.4603 868.5192) 
(list 5120.4603 868.5294) 
(list 5120.4603 868.5397) 
(list 5120.4603 868.55) 
(list 5121.142 868.55)))
(apply 'command (append '("pline") coords '("c")))
(setq tap16 (ssadd (entlast) tap16))
(command "_mirror" (entlast) "" "5120,900" "5120,901" "No")
(setq tap16 (ssadd (entlast) tap16))
(setq coords (list 
(list 5120 868.55) 
(list 5120.125 868.55) 
(list 5120.125 868.5603) 
(list 5120.125 868.5706) 
(list 5120.125 868.5808) 
(list 5120.125 868.5911) 
(list 5120.125 868.6014) 
(list 5120.125 868.6117) 
(list 5120.125 868.6219) 
(list 5120.125 868.6322) 
(list 5120.125 868.6425) 
(list 5120.125 868.6528) 
(list 5120.125 868.6631) 
(list 5120.125 868.6733) 
(list 5120.125 868.6836) 
(list 5120.125 868.6939) 
(list 5120.125 868.7042) 
(list 5120.125 868.7144) 
(list 5120.125 868.7247) 
(list 5120.125 868.735) 
(list 5120.125 868.7453) 
(list 5120.125 868.7556) 
(list 5120.125 868.7658) 
(list 5120.125 868.7761) 
(list 5120.125 868.7864) 
(list 5120.125 868.7967) 
(list 5120.125 868.8069) 
(list 5120.125 868.8172) 
(list 5120.125 868.8275) 
(list 5120.125 868.8378) 
(list 5120.125 868.8481) 
(list 5120.125 868.8583) 
(list 5120.125 868.8686) 
(list 5120.125 868.8789) 
(list 5120.125 868.8892) 
(list 5120.125 868.8994) 
(list 5120.125 868.9097) 
(list 5120.125 868.92) 
(list 5120 868.92)))
(apply 'command (append '("pline") coords '("c")))
(setq tap16 (ssadd (entlast) tap16))
(command "_mirror" (entlast) "" "5120,900" "5120,901" "No")
(setq tap16 (ssadd (entlast) tap16))
(setq coords (list 
(list 5120.4714 868.55) 
(list 5120.4603 868.55) 
(list 5120.4599 868.5603) 
(list 5120.4581 868.5706) 
(list 5120.4548 868.5808) 
(list 5120.4502 868.5911) 
(list 5120.4445 868.6014) 
(list 5120.4377 868.6117) 
(list 5120.4301 868.6219) 
(list 5120.4219 868.6322) 
(list 5120.4134 868.6425) 
(list 5120.4048 868.6528) 
(list 5120.3963 868.6631) 
(list 5120.3883 868.6733) 
(list 5120.381 868.6836) 
(list 5120.3745 868.6939) 
(list 5120.3693 868.7042) 
(list 5120.3653 868.7144) 
(list 5120.3627 868.7247) 
(list 5120.3617 868.735) 
(list 5120.3623 868.7453) 
(list 5120.3645 868.7556) 
(list 5120.3682 868.7658) 
(list 5120.3733 868.7761) 
(list 5120.3797 868.7864) 
(list 5120.3872 868.7967) 
(list 5120.3957 868.8069) 
(list 5120.4047 868.8172) 
(list 5120.4142 868.8275) 
(list 5120.4237 868.8378) 
(list 5120.4331 868.8481) 
(list 5120.4419 868.8583) 
(list 5120.45 868.8686) 
(list 5120.4571 868.8789) 
(list 5120.463 868.8892) 
(list 5120.4674 868.8994) 
(list 5120.4702 868.9097) 
(list 5120.4714 868.92) 
(list 5120.4714 868.92)))
(apply 'command (append '("pline") coords '("c")))
(setq tap16 (ssadd (entlast) tap16))
(command "_mirror" (entlast) "" "5120,900" "5120,901" "No")
(setq tap16 (ssadd (entlast) tap16))
(setq coords (list 
(list 5121.142 868.55) 
(list 5120.4714 868.55) 
(list 5120.4714 868.5603) 
(list 5120.4714 868.5706) 
(list 5120.4714 868.5808) 
(list 5120.4714 868.5911) 
(list 5120.4714 868.6014) 
(list 5120.4714 868.6117) 
(list 5120.4714 868.6219) 
(list 5120.4714 868.6322) 
(list 5120.4714 868.6425) 
(list 5120.4714 868.6528) 
(list 5120.4714 868.6631) 
(list 5120.4714 868.6733) 
(list 5120.4714 868.6836) 
(list 5120.4714 868.6939) 
(list 5120.4714 868.7042) 
(list 5120.4714 868.7144) 
(list 5120.4714 868.7247) 
(list 5120.4714 868.735) 
(list 5120.4714 868.7453) 
(list 5120.4714 868.7556) 
(list 5120.4714 868.7658) 
(list 5120.4714 868.7761) 
(list 5120.4714 868.7864) 
(list 5120.4714 868.7967) 
(list 5120.4714 868.8069) 
(list 5120.4714 868.8172) 
(list 5120.4714 868.8275) 
(list 5120.4714 868.8378) 
(list 5120.4714 868.8481) 
(list 5120.4714 868.8583) 
(list 5120.4714 868.8686) 
(list 5120.4714 868.8789) 
(list 5120.4714 868.8892) 
(list 5120.4714 868.8994) 
(list 5120.4714 868.9097) 
(list 5120.4714 868.92) 
(list 5121.142 868.92)))
(apply 'command (append '("pline") coords '("c")))
(setq tap16 (ssadd (entlast) tap16))
(command "_mirror" (entlast) "" "5120,900" "5120,901" "No")
(setq tap16 (ssadd (entlast) tap16))
(setq coords (list 
(list 5120 868.92) 
(list 5120.125 868.92) 
(list 5120.125 868.9303) 
(list 5120.125 868.9406) 
(list 5120.125 868.9508) 
(list 5120.125 868.9611) 
(list 5120.125 868.9714) 
(list 5120.125 868.9817) 
(list 5120.125 868.9919) 
(list 5120.125 869.0022) 
(list 5120.125 869.0125) 
(list 5120.125 869.0228) 
(list 5120.125 869.0331) 
(list 5120.125 869.0433) 
(list 5120.125 869.0536) 
(list 5120.125 869.0639) 
(list 5120.125 869.0742) 
(list 5120.125 869.0844) 
(list 5120.125 869.0947) 
(list 5120.125 869.105) 
(list 5120.125 869.1153) 
(list 5120.125 869.1256) 
(list 5120.125 869.1358) 
(list 5120.125 869.1461) 
(list 5120.125 869.1564) 
(list 5120.125 869.1667) 
(list 5120.125 869.1769) 
(list 5120.125 869.1872) 
(list 5120.125 869.1975) 
(list 5120.125 869.2078) 
(list 5120.125 869.2181) 
(list 5120.125 869.2283) 
(list 5120.125 869.2386) 
(list 5120.125 869.2489) 
(list 5120.125 869.2592) 
(list 5120.125 869.2694) 
(list 5120.125 869.2797) 
(list 5120.125 869.29) 
(list 5120 869.29)))
(apply 'command (append '("pline") coords '("c")))
(setq tap16 (ssadd (entlast) tap16))
(command "_mirror" (entlast) "" "5120,900" "5120,901" "No")
(setq tap16 (ssadd (entlast) tap16))
(setq coords (list 
(list 5120.4825 868.92) 
(list 5120.4714 868.92) 
(list 5120.4708 868.9303) 
(list 5120.4686 868.9406) 
(list 5120.4646 868.9508) 
(list 5120.4591 868.9611) 
(list 5120.4522 868.9714) 
(list 5120.4441 868.9817) 
(list 5120.435 868.9919) 
(list 5120.4252 869.0022) 
(list 5120.415 869.0125) 
(list 5120.4047 869.0228) 
(list 5120.3947 869.0331) 
(list 5120.3852 869.0433) 
(list 5120.3765 869.0536) 
(list 5120.3689 869.0639) 
(list 5120.3627 869.0742) 
(list 5120.358 869.0844) 
(list 5120.355 869.0947) 
(list 5120.3539 869.105) 
(list 5120.3546 869.1153) 
(list 5120.3572 869.1256) 
(list 5120.3616 869.1358) 
(list 5120.3676 869.1461) 
(list 5120.3752 869.1564) 
(list 5120.3841 869.1667) 
(list 5120.394 869.1769) 
(list 5120.4047 869.1872) 
(list 5120.4158 869.1975) 
(list 5120.427 869.2078) 
(list 5120.4379 869.2181) 
(list 5120.4483 869.2283) 
(list 5120.4577 869.2386) 
(list 5120.466 869.2489) 
(list 5120.4728 869.2592) 
(list 5120.4779 869.2694) 
(list 5120.4812 869.2797) 
(list 5120.4825 869.29) 
(list 5120.4825 869.29)))
(apply 'command (append '("pline") coords '("c")))
(setq tap16 (ssadd (entlast) tap16))
(command "_mirror" (entlast) "" "5120,900" "5120,901" "No")
(setq tap16 (ssadd (entlast) tap16))
(setq coords (list 
(list 5121.142 868.92) 
(list 5120.4825 868.92) 
(list 5120.4825 868.9303) 
(list 5120.4825 868.9406) 
(list 5120.4825 868.9508) 
(list 5120.4825 868.9611) 
(list 5120.4825 868.9714) 
(list 5120.4825 868.9817) 
(list 5120.4825 868.9919) 
(list 5120.4825 869.0022) 
(list 5120.4825 869.0125) 
(list 5120.4825 869.0228) 
(list 5120.4825 869.0331) 
(list 5120.4825 869.0433) 
(list 5120.4825 869.0536) 
(list 5120.4825 869.0639) 
(list 5120.4825 869.0742) 
(list 5120.4825 869.0844) 
(list 5120.4825 869.0947) 
(list 5120.4825 869.105) 
(list 5120.4825 869.1153) 
(list 5120.4825 869.1256) 
(list 5120.4825 869.1358) 
(list 5120.4825 869.1461) 
(list 5120.4825 869.1564) 
(list 5120.4825 869.1667) 
(list 5120.4825 869.1769) 
(list 5120.4825 869.1872) 
(list 5120.4825 869.1975) 
(list 5120.4825 869.2078) 
(list 5120.4825 869.2181) 
(list 5120.4825 869.2283) 
(list 5120.4825 869.2386) 
(list 5120.4825 869.2489) 
(list 5120.4825 869.2592) 
(list 5120.4825 869.2694) 
(list 5120.4825 869.2797) 
(list 5120.4825 869.29) 
(list 5121.142 869.29)))
(apply 'command (append '("pline") coords '("c")))
(setq tap16 (ssadd (entlast) tap16))
(command "_mirror" (entlast) "" "5120,900" "5120,901" "No")
(setq tap16 (ssadd (entlast) tap16))
(setq coords (list 
(list 5120 869.29) 
(list 5120.125 869.29) 
(list 5120.125 869.3003) 
(list 5120.125 869.3106) 
(list 5120.125 869.3208) 
(list 5120.125 869.3311) 
(list 5120.125 869.3414) 
(list 5120.125 869.3517) 
(list 5120.125 869.3619) 
(list 5120.125 869.3722) 
(list 5120.125 869.3825) 
(list 5120.125 869.3928) 
(list 5120.125 869.4031) 
(list 5120.125 869.4133) 
(list 5120.125 869.4236) 
(list 5120.125 869.4339) 
(list 5120.125 869.4442) 
(list 5120.125 869.4544) 
(list 5120.125 869.4647) 
(list 5120.125 869.475) 
(list 5120.125 869.4853) 
(list 5120.125 869.4956) 
(list 5120.125 869.5058) 
(list 5120.125 869.5161) 
(list 5120.125 869.5264) 
(list 5120.125 869.5367) 
(list 5120.125 869.5469) 
(list 5120.125 869.5572) 
(list 5120.125 869.5675) 
(list 5120.125 869.5778) 
(list 5120.125 869.5881) 
(list 5120.125 869.5983) 
(list 5120.125 869.6086) 
(list 5120.125 869.6189) 
(list 5120.125 869.6292) 
(list 5120.125 869.6394) 
(list 5120.125 869.6497) 
(list 5120.125 869.66) 
(list 5120 869.66)))
(apply 'command (append '("pline") coords '("c")))
(setq tap16 (ssadd (entlast) tap16))
(command "_mirror" (entlast) "" "5120,900" "5120,901" "No")
(setq tap16 (ssadd (entlast) tap16))
(setq coords (list 
(list 5120.4935 869.29) 
(list 5120.4825 869.29) 
(list 5120.4818 869.3003) 
(list 5120.4791 869.3106) 
(list 5120.4744 869.3208) 
(list 5120.4679 869.3311) 
(list 5120.4599 869.3414) 
(list 5120.4504 869.3517) 
(list 5120.4398 869.3619) 
(list 5120.4284 869.3722) 
(list 5120.4166 869.3825) 
(list 5120.4047 869.3928) 
(list 5120.393 869.4031) 
(list 5120.382 869.4133) 
(list 5120.372 869.4236) 
(list 5120.3632 869.4339) 
(list 5120.3561 869.4442) 
(list 5120.3507 869.4544) 
(list 5120.3473 869.4647) 
(list 5120.346 869.475) 
(list 5120.3469 869.4853) 
(list 5120.3499 869.4956) 
(list 5120.355 869.5058) 
(list 5120.362 869.5161) 
(list 5120.3707 869.5264) 
(list 5120.381 869.5367) 
(list 5120.3924 869.5469) 
(list 5120.4047 869.5572) 
(list 5120.4174 869.5675) 
(list 5120.4302 869.5778) 
(list 5120.4428 869.5881) 
(list 5120.4546 869.5983) 
(list 5120.4654 869.6086) 
(list 5120.4748 869.6189) 
(list 5120.4826 869.6292) 
(list 5120.4884 869.6394) 
(list 5120.4921 869.6497) 
(list 5120.4935 869.66) 
(list 5120.4935 869.66)))
(apply 'command (append '("pline") coords '("c")))
(setq tap16 (ssadd (entlast) tap16))
(command "_mirror" (entlast) "" "5120,900" "5120,901" "No")
(setq tap16 (ssadd (entlast) tap16))
(setq coords (list 
(list 5121.142 869.29) 
(list 5120.4935 869.29) 
(list 5120.4935 869.3003) 
(list 5120.4935 869.3106) 
(list 5120.4935 869.3208) 
(list 5120.4935 869.3311) 
(list 5120.4935 869.3414) 
(list 5120.4935 869.3517) 
(list 5120.4935 869.3619) 
(list 5120.4935 869.3722) 
(list 5120.4935 869.3825) 
(list 5120.4935 869.3928) 
(list 5120.4935 869.4031) 
(list 5120.4935 869.4133) 
(list 5120.4935 869.4236) 
(list 5120.4935 869.4339) 
(list 5120.4935 869.4442) 
(list 5120.4935 869.4544) 
(list 5120.4935 869.4647) 
(list 5120.4935 869.475) 
(list 5120.4935 869.4853) 
(list 5120.4935 869.4956) 
(list 5120.4935 869.5058) 
(list 5120.4935 869.5161) 
(list 5120.4935 869.5264) 
(list 5120.4935 869.5367) 
(list 5120.4935 869.5469) 
(list 5120.4935 869.5572) 
(list 5120.4935 869.5675) 
(list 5120.4935 869.5778) 
(list 5120.4935 869.5881) 
(list 5120.4935 869.5983) 
(list 5120.4935 869.6086) 
(list 5120.4935 869.6189) 
(list 5120.4935 869.6292) 
(list 5120.4935 869.6394) 
(list 5120.4935 869.6497) 
(list 5120.4935 869.66) 
(list 5121.142 869.66)))
(apply 'command (append '("pline") coords '("c")))
(setq tap16 (ssadd (entlast) tap16))
(command "_mirror" (entlast) "" "5120,900" "5120,901" "No")
(setq tap16 (ssadd (entlast) tap16))
(setq coords (list 
(list 5120 869.66) 
(list 5120.125 869.66) 
(list 5120.125 869.6703) 
(list 5120.125 869.6806) 
(list 5120.125 869.6908) 
(list 5120.125 869.7011) 
(list 5120.125 869.7114) 
(list 5120.125 869.7217) 
(list 5120.125 869.7319) 
(list 5120.125 869.7422) 
(list 5120.125 869.7525) 
(list 5120.125 869.7628) 
(list 5120.125 869.7731) 
(list 5120.125 869.7833) 
(list 5120.125 869.7936) 
(list 5120.125 869.8039) 
(list 5120.125 869.8142) 
(list 5120.125 869.8244) 
(list 5120.125 869.8347) 
(list 5120.125 869.845) 
(list 5120.125 869.8553) 
(list 5120.125 869.8656) 
(list 5120.125 869.8758) 
(list 5120.125 869.8861) 
(list 5120.125 869.8964) 
(list 5120.125 869.9067) 
(list 5120.125 869.9169) 
(list 5120.125 869.9272) 
(list 5120.125 869.9375) 
(list 5120.125 869.9478) 
(list 5120.125 869.9581) 
(list 5120.125 869.9683) 
(list 5120.125 869.9786) 
(list 5120.125 869.9889) 
(list 5120.125 869.9992) 
(list 5120.125 870.0094) 
(list 5120.125 870.0197) 
(list 5120.125 870.03) 
(list 5120 870.03)))
(apply 'command (append '("pline") coords '("c")))
(setq tap16 (ssadd (entlast) tap16))
(command "_mirror" (entlast) "" "5120,900" "5120,901" "No")
(setq tap16 (ssadd (entlast) tap16))
(setq coords (list 
(list 5120.5046 869.66) 
(list 5120.4935 869.66) 
(list 5120.4927 869.6703) 
(list 5120.4895 869.6806) 
(list 5120.4842 869.6908) 
(list 5120.4768 869.7011) 
(list 5120.4675 869.7114) 
(list 5120.4567 869.7217) 
(list 5120.4446 869.7319) 
(list 5120.4317 869.7422) 
(list 5120.4182 869.7525) 
(list 5120.4046 869.7628) 
(list 5120.3914 869.7731) 
(list 5120.3789 869.7833) 
(list 5120.3675 869.7936) 
(list 5120.3576 869.8039) 
(list 5120.3495 869.8142) 
(list 5120.3434 869.8244) 
(list 5120.3396 869.8347) 
(list 5120.3381 869.845) 
(list 5120.3391 869.8553) 
(list 5120.3426 869.8656) 
(list 5120.3484 869.8758) 
(list 5120.3563 869.8861) 
(list 5120.3663 869.8964) 
(list 5120.3778 869.9067) 
(list 5120.3908 869.9169) 
(list 5120.4046 869.9272) 
(list 5120.419 869.9375) 
(list 5120.4335 869.9478) 
(list 5120.4476 869.9581) 
(list 5120.4609 869.9683) 
(list 5120.4731 869.9786) 
(list 5120.4837 869.9889) 
(list 5120.4924 869.9992) 
(list 5120.4989 870.0094) 
(list 5120.503 870.0197) 
(list 5120.5046 870.03) 
(list 5120.5046 870.03)))
(apply 'command (append '("pline") coords '("c")))
(setq tap16 (ssadd (entlast) tap16))
(command "_mirror" (entlast) "" "5120,900" "5120,901" "No")
(setq tap16 (ssadd (entlast) tap16))
(setq coords (list 
(list 5121.142 869.66) 
(list 5120.5046 869.66) 
(list 5120.5046 869.6703) 
(list 5120.5046 869.6806) 
(list 5120.5046 869.6908) 
(list 5120.5046 869.7011) 
(list 5120.5046 869.7114) 
(list 5120.5046 869.7217) 
(list 5120.5046 869.7319) 
(list 5120.5046 869.7422) 
(list 5120.5046 869.7525) 
(list 5120.5046 869.7628) 
(list 5120.5046 869.7731) 
(list 5120.5046 869.7833) 
(list 5120.5046 869.7936) 
(list 5120.5046 869.8039) 
(list 5120.5046 869.8142) 
(list 5120.5046 869.8244) 
(list 5120.5046 869.8347) 
(list 5120.5046 869.845) 
(list 5120.5046 869.8553) 
(list 5120.5046 869.8656) 
(list 5120.5046 869.8758) 
(list 5120.5046 869.8861) 
(list 5120.5046 869.8964) 
(list 5120.5046 869.9067) 
(list 5120.5046 869.9169) 
(list 5120.5046 869.9272) 
(list 5120.5046 869.9375) 
(list 5120.5046 869.9478) 
(list 5120.5046 869.9581) 
(list 5120.5046 869.9683) 
(list 5120.5046 869.9786) 
(list 5120.5046 869.9889) 
(list 5120.5046 869.9992) 
(list 5120.5046 870.0094) 
(list 5120.5046 870.0197) 
(list 5120.5046 870.03) 
(list 5121.142 870.03)))
(apply 'command (append '("pline") coords '("c")))
(setq tap16 (ssadd (entlast) tap16))
(command "_mirror" (entlast) "" "5120,900" "5120,901" "No")
(setq tap16 (ssadd (entlast) tap16))
(setq coords (list 
(list 5120 870.03) 
(list 5120.125 870.03) 
(list 5120.125 870.0403) 
(list 5120.125 870.0506) 
(list 5120.125 870.0608) 
(list 5120.125 870.0711) 
(list 5120.125 870.0814) 
(list 5120.125 870.0917) 
(list 5120.125 870.1019) 
(list 5120.125 870.1122) 
(list 5120.125 870.1225) 
(list 5120.125 870.1328) 
(list 5120.125 870.1431) 
(list 5120.125 870.1533) 
(list 5120.125 870.1636) 
(list 5120.125 870.1739) 
(list 5120.125 870.1842) 
(list 5120.125 870.1944) 
(list 5120.125 870.2047) 
(list 5120.125 870.215) 
(list 5120.125 870.2253) 
(list 5120.125 870.2356) 
(list 5120.125 870.2458) 
(list 5120.125 870.2561) 
(list 5120.125 870.2664) 
(list 5120.125 870.2767) 
(list 5120.125 870.2869) 
(list 5120.125 870.2972) 
(list 5120.125 870.3075) 
(list 5120.125 870.3178) 
(list 5120.125 870.3281) 
(list 5120.125 870.3383) 
(list 5120.125 870.3486) 
(list 5120.125 870.3589) 
(list 5120.125 870.3692) 
(list 5120.125 870.3794) 
(list 5120.125 870.3897) 
(list 5120.125 870.4) 
(list 5120 870.4)))
(apply 'command (append '("pline") coords '("c")))
(setq tap16 (ssadd (entlast) tap16))
(command "_mirror" (entlast) "" "5120,900" "5120,901" "No")
(setq tap16 (ssadd (entlast) tap16))
(setq coords (list 
(list 5120.5157 870.03) 
(list 5120.5046 870.03) 
(list 5120.5036 870.0403) 
(list 5120.5 870.0506) 
(list 5120.494 870.0608) 
(list 5120.4857 870.0711) 
(list 5120.4752 870.0814) 
(list 5120.4631 870.0917) 
(list 5120.4495 870.1019) 
(list 5120.4349 870.1122) 
(list 5120.4198 870.1225) 
(list 5120.4046 870.1328) 
(list 5120.3898 870.1431) 
(list 5120.3758 870.1533) 
(list 5120.363 870.1636) 
(list 5120.3519 870.1739) 
(list 5120.3429 870.1842) 
(list 5120.3361 870.1944) 
(list 5120.3318 870.2047) 
(list 5120.3303 870.215) 
(list 5120.3314 870.2253) 
(list 5120.3353 870.2356) 
(list 5120.3418 870.2458) 
(list 5120.3507 870.2561) 
(list 5120.3618 870.2664) 
(list 5120.3747 870.2767) 
(list 5120.3891 870.2869) 
(list 5120.4046 870.2972) 
(list 5120.4206 870.3075) 
(list 5120.4367 870.3178) 
(list 5120.4524 870.3281) 
(list 5120.4673 870.3383) 
(list 5120.4808 870.3486) 
(list 5120.4925 870.3589) 
(list 5120.5022 870.3692) 
(list 5120.5094 870.3794) 
(list 5120.5139 870.3897) 
(list 5120.5157 870.4) 
(list 5120.5157 870.4)))
(apply 'command (append '("pline") coords '("c")))
(setq tap16 (ssadd (entlast) tap16))
(command "_mirror" (entlast) "" "5120,900" "5120,901" "No")
(setq tap16 (ssadd (entlast) tap16))
(setq coords (list 
(list 5121.142 870.03) 
(list 5120.5157 870.03) 
(list 5120.5157 870.0403) 
(list 5120.5157 870.0506) 
(list 5120.5157 870.0608) 
(list 5120.5157 870.0711) 
(list 5120.5157 870.0814) 
(list 5120.5157 870.0917) 
(list 5120.5157 870.1019) 
(list 5120.5157 870.1122) 
(list 5120.5157 870.1225) 
(list 5120.5157 870.1328) 
(list 5120.5157 870.1431) 
(list 5120.5157 870.1533) 
(list 5120.5157 870.1636) 
(list 5120.5157 870.1739) 
(list 5120.5157 870.1842) 
(list 5120.5157 870.1944) 
(list 5120.5157 870.2047) 
(list 5120.5157 870.215) 
(list 5120.5157 870.2253) 
(list 5120.5157 870.2356) 
(list 5120.5157 870.2458) 
(list 5120.5157 870.2561) 
(list 5120.5157 870.2664) 
(list 5120.5157 870.2767) 
(list 5120.5157 870.2869) 
(list 5120.5157 870.2972) 
(list 5120.5157 870.3075) 
(list 5120.5157 870.3178) 
(list 5120.5157 870.3281) 
(list 5120.5157 870.3383) 
(list 5120.5157 870.3486) 
(list 5120.5157 870.3589) 
(list 5120.5157 870.3692) 
(list 5120.5157 870.3794) 
(list 5120.5157 870.3897) 
(list 5120.5157 870.4) 
(list 5121.142 870.4)))
(apply 'command (append '("pline") coords '("c")))
(setq tap16 (ssadd (entlast) tap16))
(command "_mirror" (entlast) "" "5120,900" "5120,901" "No")
(setq tap16 (ssadd (entlast) tap16))
(setq coords (list 
(list 5120 870.4) 
(list 5120.125 870.4) 
(list 5120.125 870.4103) 
(list 5120.125 870.4206) 
(list 5120.125 870.4308) 
(list 5120.125 870.4411) 
(list 5120.125 870.4514) 
(list 5120.125 870.4617) 
(list 5120.125 870.4719) 
(list 5120.125 870.4822) 
(list 5120.125 870.4925) 
(list 5120.125 870.5028) 
(list 5120.125 870.5131) 
(list 5120.125 870.5233) 
(list 5120.125 870.5336) 
(list 5120.125 870.5439) 
(list 5120.125 870.5542) 
(list 5120.125 870.5644) 
(list 5120.125 870.5747) 
(list 5120.125 870.585) 
(list 5120.125 870.5953) 
(list 5120.125 870.6056) 
(list 5120.125 870.6158) 
(list 5120.125 870.6261) 
(list 5120.125 870.6364) 
(list 5120.125 870.6467) 
(list 5120.125 870.6569) 
(list 5120.125 870.6672) 
(list 5120.125 870.6775) 
(list 5120.125 870.6878) 
(list 5120.125 870.6981) 
(list 5120.125 870.7083) 
(list 5120.125 870.7186) 
(list 5120.125 870.7289) 
(list 5120.125 870.7392) 
(list 5120.125 870.7494) 
(list 5120.125 870.7597) 
(list 5120.125 870.77) 
(list 5120 870.77)))
(apply 'command (append '("pline") coords '("c")))
(setq tap16 (ssadd (entlast) tap16))
(command "_mirror" (entlast) "" "5120,900" "5120,901" "No")
(setq tap16 (ssadd (entlast) tap16))
(setq coords (list 
(list 5120.5267 870.4) 
(list 5120.5157 870.4) 
(list 5120.5145 870.4103) 
(list 5120.5105 870.4206) 
(list 5120.5038 870.4308) 
(list 5120.4945 870.4411) 
(list 5120.4829 870.4514) 
(list 5120.4694 870.4617) 
(list 5120.4543 870.4719) 
(list 5120.4382 870.4822) 
(list 5120.4214 870.4925) 
(list 5120.4045 870.5028) 
(list 5120.3881 870.5131) 
(list 5120.3726 870.5233) 
(list 5120.3585 870.5336) 
(list 5120.3463 870.5439) 
(list 5120.3363 870.5542) 
(list 5120.3288 870.5644) 
(list 5120.3241 870.5747) 
(list 5120.3224 870.585) 
(list 5120.3237 870.5953) 
(list 5120.328 870.6056) 
(list 5120.3352 870.6158) 
(list 5120.345 870.6261) 
(list 5120.3573 870.6364) 
(list 5120.3716 870.6467) 
(list 5120.3875 870.6569) 
(list 5120.4045 870.6672) 
(list 5120.4222 870.6775) 
(list 5120.44 870.6878) 
(list 5120.4573 870.6981) 
(list 5120.4736 870.7083) 
(list 5120.4885 870.7186) 
(list 5120.5014 870.7289) 
(list 5120.512 870.7392) 
(list 5120.5199 870.7494) 
(list 5120.5248 870.7597) 
(list 5120.5267 870.77) 
(list 5120.5267 870.77)))
(apply 'command (append '("pline") coords '("c")))
(setq tap16 (ssadd (entlast) tap16))
(command "_mirror" (entlast) "" "5120,900" "5120,901" "No")
(setq tap16 (ssadd (entlast) tap16))
(setq coords (list 
(list 5121.142 870.4) 
(list 5120.5267 870.4) 
(list 5120.5267 870.4103) 
(list 5120.5267 870.4206) 
(list 5120.5267 870.4308) 
(list 5120.5267 870.4411) 
(list 5120.5267 870.4514) 
(list 5120.5267 870.4617) 
(list 5120.5267 870.4719) 
(list 5120.5267 870.4822) 
(list 5120.5267 870.4925) 
(list 5120.5267 870.5028) 
(list 5120.5267 870.5131) 
(list 5120.5267 870.5233) 
(list 5120.5267 870.5336) 
(list 5120.5267 870.5439) 
(list 5120.5267 870.5542) 
(list 5120.5267 870.5644) 
(list 5120.5267 870.5747) 
(list 5120.5267 870.585) 
(list 5120.5267 870.5953) 
(list 5120.5267 870.6056) 
(list 5120.5267 870.6158) 
(list 5120.5267 870.6261) 
(list 5120.5267 870.6364) 
(list 5120.5267 870.6467) 
(list 5120.5267 870.6569) 
(list 5120.5267 870.6672) 
(list 5120.5267 870.6775) 
(list 5120.5267 870.6878) 
(list 5120.5267 870.6981) 
(list 5120.5267 870.7083) 
(list 5120.5267 870.7186) 
(list 5120.5267 870.7289) 
(list 5120.5267 870.7392) 
(list 5120.5267 870.7494) 
(list 5120.5267 870.7597) 
(list 5120.5267 870.77) 
(list 5121.142 870.77)))
(apply 'command (append '("pline") coords '("c")))
(setq tap16 (ssadd (entlast) tap16))
(command "_mirror" (entlast) "" "5120,900" "5120,901" "No")
(setq tap16 (ssadd (entlast) tap16))
(setq coords (list 
(list 5120 870.77) 
(list 5120.125 870.77) 
(list 5120.125 870.7803) 
(list 5120.125 870.7906) 
(list 5120.125 870.8008) 
(list 5120.125 870.8111) 
(list 5120.125 870.8214) 
(list 5120.125 870.8317) 
(list 5120.125 870.8419) 
(list 5120.125 870.8522) 
(list 5120.125 870.8625) 
(list 5120.125 870.8728) 
(list 5120.125 870.8831) 
(list 5120.125 870.8933) 
(list 5120.125 870.9036) 
(list 5120.125 870.9139) 
(list 5120.125 870.9242) 
(list 5120.125 870.9344) 
(list 5120.125 870.9447) 
(list 5120.125 870.955) 
(list 5120.125 870.9653) 
(list 5120.125 870.9756) 
(list 5120.125 870.9858) 
(list 5120.125 870.9961) 
(list 5120.125 871.0064) 
(list 5120.125 871.0167) 
(list 5120.125 871.0269) 
(list 5120.125 871.0372) 
(list 5120.125 871.0475) 
(list 5120.125 871.0578) 
(list 5120.125 871.0681) 
(list 5120.125 871.0783) 
(list 5120.125 871.0886) 
(list 5120.125 871.0989) 
(list 5120.125 871.1092) 
(list 5120.125 871.1194) 
(list 5120.125 871.1297) 
(list 5120.125 871.14) 
(list 5120 871.14)))
(apply 'command (append '("pline") coords '("c")))
(setq tap16 (ssadd (entlast) tap16))
(command "_mirror" (entlast) "" "5120,900" "5120,901" "No")
(setq tap16 (ssadd (entlast) tap16))
(setq coords (list 
(list 5120.5378 870.77) 
(list 5120.5267 870.77) 
(list 5120.5255 870.7803) 
(list 5120.521 870.7906) 
(list 5120.5136 870.8008) 
(list 5120.5034 870.8111) 
(list 5120.4906 870.8214) 
(list 5120.4757 870.8317) 
(list 5120.4592 870.8419) 
(list 5120.4414 870.8522) 
(list 5120.423 870.8625) 
(list 5120.4045 870.8728) 
(list 5120.3865 870.8831) 
(list 5120.3695 870.8933) 
(list 5120.354 870.9036) 
(list 5120.3406 870.9139) 
(list 5120.3297 870.9242) 
(list 5120.3215 870.9344) 
(list 5120.3164 870.9447) 
(list 5120.3145 870.955) 
(list 5120.316 870.9653) 
(list 5120.3207 870.9756) 
(list 5120.3286 870.9858) 
(list 5120.3394 870.9961) 
(list 5120.3528 871.0064) 
(list 5120.3684 871.0167) 
(list 5120.3858 871.0269) 
(list 5120.4045 871.0372) 
(list 5120.4238 871.0475) 
(list 5120.4432 871.0578) 
(list 5120.4621 871.0681) 
(list 5120.4799 871.0783) 
(list 5120.4962 871.0886) 
(list 5120.5102 871.0989) 
(list 5120.5218 871.1092) 
(list 5120.5304 871.1194) 
(list 5120.5358 871.1297) 
(list 5120.5378 871.14) 
(list 5120.5378 871.14)))
(apply 'command (append '("pline") coords '("c")))
(setq tap16 (ssadd (entlast) tap16))
(command "_mirror" (entlast) "" "5120,900" "5120,901" "No")
(setq tap16 (ssadd (entlast) tap16))
(setq coords (list 
(list 5121.142 870.77) 
(list 5120.5378 870.77) 
(list 5120.5378 870.7803) 
(list 5120.5378 870.7906) 
(list 5120.5378 870.8008) 
(list 5120.5378 870.8111) 
(list 5120.5378 870.8214) 
(list 5120.5378 870.8317) 
(list 5120.5378 870.8419) 
(list 5120.5378 870.8522) 
(list 5120.5378 870.8625) 
(list 5120.5378 870.8728) 
(list 5120.5378 870.8831) 
(list 5120.5378 870.8933) 
(list 5120.5378 870.9036) 
(list 5120.5378 870.9139) 
(list 5120.5378 870.9242) 
(list 5120.5378 870.9344) 
(list 5120.5378 870.9447) 
(list 5120.5378 870.955) 
(list 5120.5378 870.9653) 
(list 5120.5378 870.9756) 
(list 5120.5378 870.9858) 
(list 5120.5378 870.9961) 
(list 5120.5378 871.0064) 
(list 5120.5378 871.0167) 
(list 5120.5378 871.0269) 
(list 5120.5378 871.0372) 
(list 5120.5378 871.0475) 
(list 5120.5378 871.0578) 
(list 5120.5378 871.0681) 
(list 5120.5378 871.0783) 
(list 5120.5378 871.0886) 
(list 5120.5378 871.0989) 
(list 5120.5378 871.1092) 
(list 5120.5378 871.1194) 
(list 5120.5378 871.1297) 
(list 5120.5378 871.14) 
(list 5121.142 871.14)))
(apply 'command (append '("pline") coords '("c")))
(setq tap16 (ssadd (entlast) tap16))
(command "_mirror" (entlast) "" "5120,900" "5120,901" "No")
(setq tap16 (ssadd (entlast) tap16))
(setq coords (list 
(list 5120 871.14) 
(list 5120.125 871.14) 
(list 5120.125 871.1503) 
(list 5120.125 871.1606) 
(list 5120.125 871.1708) 
(list 5120.125 871.1811) 
(list 5120.125 871.1914) 
(list 5120.125 871.2017) 
(list 5120.125 871.2119) 
(list 5120.125 871.2222) 
(list 5120.125 871.2325) 
(list 5120.125 871.2428) 
(list 5120.125 871.2531) 
(list 5120.125 871.2633) 
(list 5120.125 871.2736) 
(list 5120.125 871.2839) 
(list 5120.125 871.2942) 
(list 5120.125 871.3044) 
(list 5120.125 871.3147) 
(list 5120.125 871.325) 
(list 5120.125 871.3353) 
(list 5120.125 871.3456) 
(list 5120.125 871.3558) 
(list 5120.125 871.3661) 
(list 5120.125 871.3764) 
(list 5120.125 871.3867) 
(list 5120.125 871.3969) 
(list 5120.125 871.4072) 
(list 5120.125 871.4175) 
(list 5120.125 871.4278) 
(list 5120.125 871.4381) 
(list 5120.125 871.4483) 
(list 5120.125 871.4586) 
(list 5120.125 871.4689) 
(list 5120.125 871.4792) 
(list 5120.125 871.4894) 
(list 5120.125 871.4997) 
(list 5120.125 871.51) 
(list 5120 871.51)))
(apply 'command (append '("pline") coords '("c")))
(setq tap16 (ssadd (entlast) tap16))
(command "_mirror" (entlast) "" "5120,900" "5120,901" "No")
(setq tap16 (ssadd (entlast) tap16))
(setq coords (list 
(list 5120.5489 871.14) 
(list 5120.5378 871.14) 
(list 5120.5364 871.1503) 
(list 5120.5315 871.1606) 
(list 5120.5234 871.1708) 
(list 5120.5122 871.1811) 
(list 5120.4983 871.1914) 
(list 5120.4821 871.2017) 
(list 5120.464 871.2119) 
(list 5120.4446 871.2222) 
(list 5120.4246 871.2325) 
(list 5120.4045 871.2428) 
(list 5120.3848 871.2531) 
(list 5120.3664 871.2633) 
(list 5120.3496 871.2736) 
(list 5120.335 871.2839) 
(list 5120.3231 871.2942) 
(list 5120.3142 871.3044) 
(list 5120.3087 871.3147) 
(list 5120.3067 871.325) 
(list 5120.3082 871.3353) 
(list 5120.3134 871.3456) 
(list 5120.322 871.3558) 
(list 5120.3337 871.3661) 
(list 5120.3483 871.3764) 
(list 5120.3653 871.3867) 
(list 5120.3842 871.3969) 
(list 5120.4044 871.4072) 
(list 5120.4254 871.4175) 
(list 5120.4465 871.4278) 
(list 5120.467 871.4381) 
(list 5120.4863 871.4483) 
(list 5120.5038 871.4586) 
(list 5120.5191 871.4689) 
(list 5120.5316 871.4792) 
(list 5120.5409 871.4894) 
(list 5120.5467 871.4997) 
(list 5120.5489 871.51) 
(list 5120.5489 871.51)))
(apply 'command (append '("pline") coords '("c")))
(setq tap16 (ssadd (entlast) tap16))
(command "_mirror" (entlast) "" "5120,900" "5120,901" "No")
(setq tap16 (ssadd (entlast) tap16))
(setq coords (list 
(list 5121.142 871.14) 
(list 5120.5489 871.14) 
(list 5120.5489 871.1503) 
(list 5120.5489 871.1606) 
(list 5120.5489 871.1708) 
(list 5120.5489 871.1811) 
(list 5120.5489 871.1914) 
(list 5120.5489 871.2017) 
(list 5120.5489 871.2119) 
(list 5120.5489 871.2222) 
(list 5120.5489 871.2325) 
(list 5120.5489 871.2428) 
(list 5120.5489 871.2531) 
(list 5120.5489 871.2633) 
(list 5120.5489 871.2736) 
(list 5120.5489 871.2839) 
(list 5120.5489 871.2942) 
(list 5120.5489 871.3044) 
(list 5120.5489 871.3147) 
(list 5120.5489 871.325) 
(list 5120.5489 871.3353) 
(list 5120.5489 871.3456) 
(list 5120.5489 871.3558) 
(list 5120.5489 871.3661) 
(list 5120.5489 871.3764) 
(list 5120.5489 871.3867) 
(list 5120.5489 871.3969) 
(list 5120.5489 871.4072) 
(list 5120.5489 871.4175) 
(list 5120.5489 871.4278) 
(list 5120.5489 871.4381) 
(list 5120.5489 871.4483) 
(list 5120.5489 871.4586) 
(list 5120.5489 871.4689) 
(list 5120.5489 871.4792) 
(list 5120.5489 871.4894) 
(list 5120.5489 871.4997) 
(list 5120.5489 871.51) 
(list 5121.142 871.51)))
(apply 'command (append '("pline") coords '("c")))
(setq tap16 (ssadd (entlast) tap16))
(command "_mirror" (entlast) "" "5120,900" "5120,901" "No")
(setq tap16 (ssadd (entlast) tap16))
(setq coords (list 
(list 5120 871.51) 
(list 5120.125 871.51) 
(list 5120.125 871.5203) 
(list 5120.125 871.5306) 
(list 5120.125 871.5408) 
(list 5120.125 871.5511) 
(list 5120.125 871.5614) 
(list 5120.125 871.5717) 
(list 5120.125 871.5819) 
(list 5120.125 871.5922) 
(list 5120.125 871.6025) 
(list 5120.125 871.6128) 
(list 5120.125 871.6231) 
(list 5120.125 871.6333) 
(list 5120.125 871.6436) 
(list 5120.125 871.6539) 
(list 5120.125 871.6642) 
(list 5120.125 871.6744) 
(list 5120.125 871.6847) 
(list 5120.125 871.695) 
(list 5120.125 871.7053) 
(list 5120.125 871.7156) 
(list 5120.125 871.7258) 
(list 5120.125 871.7361) 
(list 5120.125 871.7464) 
(list 5120.125 871.7567) 
(list 5120.125 871.7669) 
(list 5120.125 871.7772) 
(list 5120.125 871.7875) 
(list 5120.125 871.7978) 
(list 5120.125 871.8081) 
(list 5120.125 871.8183) 
(list 5120.125 871.8286) 
(list 5120.125 871.8389) 
(list 5120.125 871.8492) 
(list 5120.125 871.8594) 
(list 5120.125 871.8697) 
(list 5120.125 871.88) 
(list 5120 871.88)))
(apply 'command (append '("pline") coords '("c")))
(setq tap16 (ssadd (entlast) tap16))
(command "_mirror" (entlast) "" "5120,900" "5120,901" "No")
(setq tap16 (ssadd (entlast) tap16))
(setq coords (list 
(list 5120.5599 871.51) 
(list 5120.5489 871.51) 
(list 5120.5473 871.5203) 
(list 5120.542 871.5306) 
(list 5120.5332 871.5408) 
(list 5120.5211 871.5511) 
(list 5120.506 871.5614) 
(list 5120.4884 871.5717) 
(list 5120.4688 871.5819) 
(list 5120.4479 871.5922) 
(list 5120.4262 871.6025) 
(list 5120.4044 871.6128) 
(list 5120.3832 871.6231) 
(list 5120.3632 871.6333) 
(list 5120.3451 871.6436) 
(list 5120.3293 871.6539) 
(list 5120.3165 871.6642) 
(list 5120.3069 871.6744) 
(list 5120.301 871.6847) 
(list 5120.2988 871.695) 
(list 5120.3005 871.7053) 
(list 5120.3061 871.7156) 
(list 5120.3154 871.7258) 
(list 5120.3281 871.7361) 
(list 5120.3438 871.7464) 
(list 5120.3622 871.7567) 
(list 5120.3826 871.7669) 
(list 5120.4044 871.7772) 
(list 5120.427 871.7875) 
(list 5120.4497 871.7978) 
(list 5120.4718 871.8081) 
(list 5120.4926 871.8183) 
(list 5120.5115 871.8286) 
(list 5120.5279 871.8389) 
(list 5120.5414 871.8492) 
(list 5120.5514 871.8594) 
(list 5120.5576 871.8697) 
(list 5120.5599 871.88) 
(list 5120.5599 871.88)))
(apply 'command (append '("pline") coords '("c")))
(setq tap16 (ssadd (entlast) tap16))
(command "_mirror" (entlast) "" "5120,900" "5120,901" "No")
(setq tap16 (ssadd (entlast) tap16))
(setq coords (list 
(list 5121.142 871.51) 
(list 5120.5599 871.51) 
(list 5120.5599 871.5203) 
(list 5120.5599 871.5306) 
(list 5120.5599 871.5408) 
(list 5120.5599 871.5511) 
(list 5120.5599 871.5614) 
(list 5120.5599 871.5717) 
(list 5120.5599 871.5819) 
(list 5120.5599 871.5922) 
(list 5120.5599 871.6025) 
(list 5120.5599 871.6128) 
(list 5120.5599 871.6231) 
(list 5120.5599 871.6333) 
(list 5120.5599 871.6436) 
(list 5120.5599 871.6539) 
(list 5120.5599 871.6642) 
(list 5120.5599 871.6744) 
(list 5120.5599 871.6847) 
(list 5120.5599 871.695) 
(list 5120.5599 871.7053) 
(list 5120.5599 871.7156) 
(list 5120.5599 871.7258) 
(list 5120.5599 871.7361) 
(list 5120.5599 871.7464) 
(list 5120.5599 871.7567) 
(list 5120.5599 871.7669) 
(list 5120.5599 871.7772) 
(list 5120.5599 871.7875) 
(list 5120.5599 871.7978) 
(list 5120.5599 871.8081) 
(list 5120.5599 871.8183) 
(list 5120.5599 871.8286) 
(list 5120.5599 871.8389) 
(list 5120.5599 871.8492) 
(list 5120.5599 871.8594) 
(list 5120.5599 871.8697) 
(list 5120.5599 871.88) 
(list 5121.142 871.88)))
(apply 'command (append '("pline") coords '("c")))
(setq tap16 (ssadd (entlast) tap16))
(command "_mirror" (entlast) "" "5120,900" "5120,901" "No")
(setq tap16 (ssadd (entlast) tap16))
(setq coords (list 
(list 5120 871.88) 
(list 5120.125 871.88) 
(list 5120.125 871.8903) 
(list 5120.125 871.9006) 
(list 5120.125 871.9108) 
(list 5120.125 871.9211) 
(list 5120.125 871.9314) 
(list 5120.125 871.9417) 
(list 5120.125 871.9519) 
(list 5120.125 871.9622) 
(list 5120.125 871.9725) 
(list 5120.125 871.9828) 
(list 5120.125 871.9931) 
(list 5120.125 872.0033) 
(list 5120.125 872.0136) 
(list 5120.125 872.0239) 
(list 5120.125 872.0342) 
(list 5120.125 872.0444) 
(list 5120.125 872.0547) 
(list 5120.125 872.065) 
(list 5120.125 872.0753) 
(list 5120.125 872.0856) 
(list 5120.125 872.0958) 
(list 5120.125 872.1061) 
(list 5120.125 872.1164) 
(list 5120.125 872.1267) 
(list 5120.125 872.1369) 
(list 5120.125 872.1472) 
(list 5120.125 872.1575) 
(list 5120.125 872.1678) 
(list 5120.125 872.1781) 
(list 5120.125 872.1883) 
(list 5120.125 872.1986) 
(list 5120.125 872.2089) 
(list 5120.125 872.2192) 
(list 5120.125 872.2294) 
(list 5120.125 872.2397) 
(list 5120.125 872.25) 
(list 5120 872.25)))
(apply 'command (append '("pline") coords '("c")))
(setq tap16 (ssadd (entlast) tap16))
(command "_mirror" (entlast) "" "5120,900" "5120,901" "No")
(setq tap16 (ssadd (entlast) tap16))
(setq coords (list 
(list 5120.571 871.88) 
(list 5120.5599 871.88) 
(list 5120.5582 871.8903) 
(list 5120.5525 871.9006) 
(list 5120.543 871.9108) 
(list 5120.5299 871.9211) 
(list 5120.5137 871.9314) 
(list 5120.4947 871.9417) 
(list 5120.4737 871.9519) 
(list 5120.4511 871.9622) 
(list 5120.4278 871.9725) 
(list 5120.4044 871.9828) 
(list 5120.3816 871.9931) 
(list 5120.3601 872.0033) 
(list 5120.3406 872.0136) 
(list 5120.3237 872.0239) 
(list 5120.3099 872.0342) 
(list 5120.2996 872.0444) 
(list 5120.2932 872.0547) 
(list 5120.2909 872.065) 
(list 5120.2928 872.0753) 
(list 5120.2988 872.0856) 
(list 5120.3088 872.0958) 
(list 5120.3224 872.1061) 
(list 5120.3393 872.1164) 
(list 5120.359 872.1267) 
(list 5120.3809 872.1369) 
(list 5120.4044 872.1472) 
(list 5120.4286 872.1575) 
(list 5120.4529 872.1678) 
(list 5120.4766 872.1781) 
(list 5120.4989 872.1883) 
(list 5120.5192 872.1986) 
(list 5120.5368 872.2089) 
(list 5120.5512 872.2192) 
(list 5120.5619 872.2294) 
(list 5120.5685 872.2397) 
(list 5120.571 872.25) 
(list 5120.571 872.25)))
(apply 'command (append '("pline") coords '("c")))
(setq tap16 (ssadd (entlast) tap16))
(command "_mirror" (entlast) "" "5120,900" "5120,901" "No")
(setq tap16 (ssadd (entlast) tap16))
(setq coords (list 
(list 5121.142 871.88) 
(list 5120.571 871.88) 
(list 5120.571 871.8903) 
(list 5120.571 871.9006) 
(list 5120.571 871.9108) 
(list 5120.571 871.9211) 
(list 5120.571 871.9314) 
(list 5120.571 871.9417) 
(list 5120.571 871.9519) 
(list 5120.571 871.9622) 
(list 5120.571 871.9725) 
(list 5120.571 871.9828) 
(list 5120.571 871.9931) 
(list 5120.571 872.0033) 
(list 5120.571 872.0136) 
(list 5120.571 872.0239) 
(list 5120.571 872.0342) 
(list 5120.571 872.0444) 
(list 5120.571 872.0547) 
(list 5120.571 872.065) 
(list 5120.571 872.0753) 
(list 5120.571 872.0856) 
(list 5120.571 872.0958) 
(list 5120.571 872.1061) 
(list 5120.571 872.1164) 
(list 5120.571 872.1267) 
(list 5120.571 872.1369) 
(list 5120.571 872.1472) 
(list 5120.571 872.1575) 
(list 5120.571 872.1678) 
(list 5120.571 872.1781) 
(list 5120.571 872.1883) 
(list 5120.571 872.1986) 
(list 5120.571 872.2089) 
(list 5120.571 872.2192) 
(list 5120.571 872.2294) 
(list 5120.571 872.2397) 
(list 5120.571 872.25) 
(list 5121.142 872.25)))
(apply 'command (append '("pline") coords '("c")))
(setq tap16 (ssadd (entlast) tap16))
(command "_mirror" (entlast) "" "5120,900" "5120,901" "No")
(setq tap16 (ssadd (entlast) tap16))
(command "_block" "blktap16" "5120,900" tap16 "")
(command "_insert" "blktap16" "5120,900" "1" "1" "0")
(command "_insert" "blktap16" "5120,900" "1" "1" "180")
(setq uc16 nil)
(setq uc16 (ssadd))
(setq coords (list 
(list 0 -0.185) 
(list 0.125 -0.185) 
(list 0.125 -0.17472) 
(list 0.125 -0.16444) 
(list 0.125 -0.15417) 
(list 0.125 -0.14389) 
(list 0.125 -0.13361) 
(list 0.125 -0.12333) 
(list 0.125 -0.11306) 
(list 0.125 -0.10278) 
(list 0.125 -0.0925) 
(list 0.125 -0.082222) 
(list 0.125 -0.071944) 
(list 0.125 -0.061667) 
(list 0.125 -0.051389) 
(list 0.125 -0.041111) 
(list 0.125 -0.030833) 
(list 0.125 -0.020556) 
(list 0.125 -0.010278) 
(list 0.125 0) 
(list 0.125 0.010278) 
(list 0.125 0.020556) 
(list 0.125 0.030833) 
(list 0.125 0.041111) 
(list 0.125 0.051389) 
(list 0.125 0.061667) 
(list 0.125 0.071944) 
(list 0.125 0.082222) 
(list 0.125 0.0925) 
(list 0.125 0.10278) 
(list 0.125 0.11306) 
(list 0.125 0.12333) 
(list 0.125 0.13361) 
(list 0.125 0.14389) 
(list 0.125 0.15417) 
(list 0.125 0.16444) 
(list 0.125 0.17472) 
(list 0.125 0.185) 
(list 0 0.185)))
(apply 'command (append '("pline") coords '("c")))
(setq uc16 (ssadd (entlast) uc16))
(setq coords (list 
(list 1.142 -0.185) 
(list 0.571 -0.185) 
(list 0.56884 -0.17472) 
(list 0.56244 -0.16444) 
(list 0.55198 -0.15417) 
(list 0.53778 -0.14389) 
(list 0.52028 -0.13361) 
(list 0.5 -0.12333) 
(list 0.47757 -0.11306) 
(list 0.45366 -0.10278) 
(list 0.429 -0.0925) 
(list 0.40434 -0.082222) 
(list 0.38043 -0.071944) 
(list 0.358 -0.061667) 
(list 0.33772 -0.051389) 
(list 0.32022 -0.041111) 
(list 0.30602 -0.030833) 
(list 0.29556 -0.020556) 
(list 0.28916 -0.010278) 
(list 0.287 0) 
(list 0.28916 0.010278) 
(list 0.29556 0.020556) 
(list 0.30602 0.030833) 
(list 0.32022 0.041111) 
(list 0.33772 0.051389) 
(list 0.358 0.061667) 
(list 0.38043 0.071944) 
(list 0.40434 0.082222) 
(list 0.429 0.0925) 
(list 0.45366 0.10278) 
(list 0.47757 0.11306) 
(list 0.5 0.12333) 
(list 0.52028 0.13361) 
(list 0.53778 0.14389) 
(list 0.55198 0.15417) 
(list 0.56244 0.16444) 
(list 0.56884 0.17472) 
(list 0.571 0.185) 
(list 1.142 0.185)))
(apply 'command (append '("pline") coords '("c")))
(setq uc16 (ssadd (entlast) uc16))
(command "_block" "blkuc16" "0,0.185" uc16 "")
(command "_insert" "blkuc16" "5120,872.62" "1" "1" "0")
(command "_insert" "blkuc16" "5120,872.25" "1" "1" "180")
(command "_insert" "blkuc16" "5120,872.99" "1" "1" "0")
(command "_insert" "blkuc16" "5120,872.62" "1" "1" "180")
(command "_insert" "blkuc16" "5120,873.36" "1" "1" "0")
(command "_insert" "blkuc16" "5120,872.99" "1" "1" "180")
(command "_insert" "blkuc16" "5120,873.73" "1" "1" "0")
(command "_insert" "blkuc16" "5120,873.36" "1" "1" "180")
(command "_insert" "blkuc16" "5120,874.1" "1" "1" "0")
(command "_insert" "blkuc16" "5120,873.73" "1" "1" "180")
(command "_insert" "blkuc16" "5120,874.47" "1" "1" "0")
(command "_insert" "blkuc16" "5120,874.1" "1" "1" "180")
(command "_insert" "blkuc16" "5120,874.84" "1" "1" "0")
(command "_insert" "blkuc16" "5120,874.47" "1" "1" "180")
(command "_insert" "blkuc16" "5120,875.21" "1" "1" "0")
(command "_insert" "blkuc16" "5120,874.84" "1" "1" "180")
(command "_insert" "blkuc16" "5120,875.58" "1" "1" "0")
(command "_insert" "blkuc16" "5120,875.21" "1" "1" "180")
(command "_insert" "blkuc16" "5120,875.95" "1" "1" "0")
(command "_insert" "blkuc16" "5120,875.58" "1" "1" "180")
(command "_insert" "blkuc16" "5120,876.32" "1" "1" "0")
(command "_insert" "blkuc16" "5120,875.95" "1" "1" "180")
(command "_insert" "blkuc16" "5120,876.69" "1" "1" "0")
(command "_insert" "blkuc16" "5120,876.32" "1" "1" "180")
(command "_insert" "blkuc16" "5120,877.06" "1" "1" "0")
(command "_insert" "blkuc16" "5120,876.69" "1" "1" "180")
(command "_insert" "blkuc16" "5120,877.43" "1" "1" "0")
(command "_insert" "blkuc16" "5120,877.06" "1" "1" "180")
(command "_insert" "blkuc16" "5120,877.8" "1" "1" "0")
(command "_insert" "blkuc16" "5120,877.43" "1" "1" "180")
(command "_insert" "blkuc16" "5120,878.17" "1" "1" "0")
(command "_insert" "blkuc16" "5120,877.8" "1" "1" "180")
(command "_insert" "blkuc16" "5120,878.54" "1" "1" "0")
(command "_insert" "blkuc16" "5120,878.17" "1" "1" "180")
(command "_insert" "blkuc16" "5120,878.91" "1" "1" "0")
(command "_insert" "blkuc16" "5120,878.54" "1" "1" "180")
(command "_insert" "blkuc16" "5120,879.28" "1" "1" "0")
(command "_insert" "blkuc16" "5120,878.91" "1" "1" "180")
(command "_insert" "blkuc16" "5120,879.65" "1" "1" "0")
(command "_insert" "blkuc16" "5120,879.28" "1" "1" "180")
(command "_insert" "blkuc16" "5120,880.02" "1" "1" "0")
(command "_insert" "blkuc16" "5120,879.65" "1" "1" "180")
(command "_insert" "blkuc16" "5120,880.39" "1" "1" "0")
(command "_insert" "blkuc16" "5120,880.02" "1" "1" "180")
(command "_insert" "blkuc16" "5120,880.76" "1" "1" "0")
(command "_insert" "blkuc16" "5120,880.39" "1" "1" "180")
(command "_insert" "blkuc16" "5120,881.13" "1" "1" "0")
(command "_insert" "blkuc16" "5120,880.76" "1" "1" "180")
(command "_insert" "blkuc16" "5120,881.5" "1" "1" "0")
(command "_insert" "blkuc16" "5120,881.13" "1" "1" "180")
(command "_insert" "blkuc16" "5120,881.87" "1" "1" "0")
(command "_insert" "blkuc16" "5120,881.5" "1" "1" "180")
(command "_insert" "blkuc16" "5120,882.24" "1" "1" "0")
(command "_insert" "blkuc16" "5120,881.87" "1" "1" "180")
(command "_insert" "blkuc16" "5120,882.61" "1" "1" "0")
(command "_insert" "blkuc16" "5120,882.24" "1" "1" "180")
(command "_insert" "blkuc16" "5120,882.98" "1" "1" "0")
(command "_insert" "blkuc16" "5120,882.61" "1" "1" "180")
(command "_insert" "blkuc16" "5120,883.35" "1" "1" "0")
(command "_insert" "blkuc16" "5120,882.98" "1" "1" "180")
(command "_insert" "blkuc16" "5120,883.72" "1" "1" "0")
(command "_insert" "blkuc16" "5120,883.35" "1" "1" "180")
(command "_insert" "blkuc16" "5120,884.09" "1" "1" "0")
(command "_insert" "blkuc16" "5120,883.72" "1" "1" "180")
(command "_insert" "blkuc16" "5120,884.46" "1" "1" "0")
(command "_insert" "blkuc16" "5120,884.09" "1" "1" "180")
(command "_insert" "blkuc16" "5120,884.83" "1" "1" "0")
(command "_insert" "blkuc16" "5120,884.46" "1" "1" "180")
(command "_insert" "blkuc16" "5120,885.2" "1" "1" "0")
(command "_insert" "blkuc16" "5120,884.83" "1" "1" "180")
(command "_insert" "blkuc16" "5120,885.57" "1" "1" "0")
(command "_insert" "blkuc16" "5120,885.2" "1" "1" "180")
(command "_insert" "blkuc16" "5120,885.94" "1" "1" "0")
(command "_insert" "blkuc16" "5120,885.57" "1" "1" "180")
(command "_insert" "blkuc16" "5120,886.31" "1" "1" "0")
(command "_insert" "blkuc16" "5120,885.94" "1" "1" "180")
(command "_insert" "blkuc16" "5120,886.68" "1" "1" "0")
(command "_insert" "blkuc16" "5120,886.31" "1" "1" "180")
(command "_insert" "blkuc16" "5120,887.05" "1" "1" "0")
(command "_insert" "blkuc16" "5120,886.68" "1" "1" "180")
(command "_insert" "blkuc16" "5120,887.42" "1" "1" "0")
(command "_insert" "blkuc16" "5120,887.05" "1" "1" "180")
(command "_insert" "blkuc16" "5120,887.79" "1" "1" "0")
(command "_insert" "blkuc16" "5120,887.42" "1" "1" "180")
(command "_insert" "blkuc16" "5120,888.16" "1" "1" "0")
(command "_insert" "blkuc16" "5120,887.79" "1" "1" "180")
(command "_insert" "blkuc16" "5120,888.53" "1" "1" "0")
(command "_insert" "blkuc16" "5120,888.16" "1" "1" "180")
(command "_insert" "blkuc16" "5120,888.9" "1" "1" "0")
(command "_insert" "blkuc16" "5120,888.53" "1" "1" "180")
(command "_insert" "blkuc16" "5120,889.27" "1" "1" "0")
(command "_insert" "blkuc16" "5120,888.9" "1" "1" "180")
(command "_insert" "blkuc16" "5120,889.64" "1" "1" "0")
(command "_insert" "blkuc16" "5120,889.27" "1" "1" "180")
(command "_insert" "blkuc16" "5120,890.01" "1" "1" "0")
(command "_insert" "blkuc16" "5120,889.64" "1" "1" "180")
(command "_insert" "blkuc16" "5120,890.38" "1" "1" "0")
(command "_insert" "blkuc16" "5120,890.01" "1" "1" "180")
(command "_insert" "blkuc16" "5120,890.75" "1" "1" "0")
(command "_insert" "blkuc16" "5120,890.38" "1" "1" "180")
(command "_insert" "blkuc16" "5120,891.12" "1" "1" "0")
(command "_insert" "blkuc16" "5120,890.75" "1" "1" "180")
(command "_insert" "blkuc16" "5120,891.49" "1" "1" "0")
(command "_insert" "blkuc16" "5120,891.12" "1" "1" "180")
(command "_insert" "blkuc16" "5120,891.86" "1" "1" "0")
(command "_insert" "blkuc16" "5120,891.49" "1" "1" "180")
(command "_insert" "blkuc16" "5120,892.23" "1" "1" "0")
(command "_insert" "blkuc16" "5120,891.86" "1" "1" "180")
(command "_insert" "blkuc16" "5120,892.6" "1" "1" "0")
(command "_insert" "blkuc16" "5120,892.23" "1" "1" "180")
(command "_insert" "blkuc16" "5120,892.97" "1" "1" "0")
(command "_insert" "blkuc16" "5120,892.6" "1" "1" "180")
(command "_insert" "blkuc16" "5120,893.34" "1" "1" "0")
(command "_insert" "blkuc16" "5120,892.97" "1" "1" "180")
(command "_insert" "blkuc16" "5120,893.71" "1" "1" "0")
(command "_insert" "blkuc16" "5120,893.34" "1" "1" "180")
(command "_insert" "blkuc16" "5120,894.08" "1" "1" "0")
(command "_insert" "blkuc16" "5120,893.71" "1" "1" "180")
(command "_insert" "blkuc16" "5120,894.45" "1" "1" "0")
(command "_insert" "blkuc16" "5120,894.08" "1" "1" "180")
(command "_insert" "blkuc16" "5120,894.82" "1" "1" "0")
(command "_insert" "blkuc16" "5120,894.45" "1" "1" "180")
(command "_insert" "blkuc16" "5120,895.19" "1" "1" "0")
(command "_insert" "blkuc16" "5120,894.82" "1" "1" "180")
(command "_insert" "blkuc16" "5120,895.56" "1" "1" "0")
(command "_insert" "blkuc16" "5120,895.19" "1" "1" "180")
(command "_insert" "blkuc16" "5120,895.93" "1" "1" "0")
(command "_insert" "blkuc16" "5120,895.56" "1" "1" "180")
(command "_insert" "blkuc16" "5120,896.3" "1" "1" "0")
(command "_insert" "blkuc16" "5120,895.93" "1" "1" "180")
(command "_insert" "blkuc16" "5120,896.67" "1" "1" "0")
(command "_insert" "blkuc16" "5120,896.3" "1" "1" "180")
(command "_insert" "blkuc16" "5120,897.04" "1" "1" "0")
(command "_insert" "blkuc16" "5120,896.67" "1" "1" "180")
(command "_insert" "blkuc16" "5120,897.41" "1" "1" "0")
(command "_insert" "blkuc16" "5120,897.04" "1" "1" "180")
(command "_insert" "blkuc16" "5120,897.78" "1" "1" "0")
(command "_insert" "blkuc16" "5120,897.41" "1" "1" "180")
(command "_insert" "blkuc16" "5120,898.15" "1" "1" "0")
(command "_insert" "blkuc16" "5120,897.78" "1" "1" "180")
(command "_insert" "blkuc16" "5120,898.52" "1" "1" "0")
(command "_insert" "blkuc16" "5120,898.15" "1" "1" "180")
(command "_insert" "blkuc16" "5120,898.89" "1" "1" "0")
(command "_insert" "blkuc16" "5120,898.52" "1" "1" "180")
(command "_insert" "blkuc16" "5120,899.26" "1" "1" "0")
(command "_insert" "blkuc16" "5120,898.89" "1" "1" "180")
(command "_insert" "blkuc16" "5120,899.63" "1" "1" "0")
(command "_insert" "blkuc16" "5120,899.26" "1" "1" "180")
(command "_insert" "blkuc16" "5120,900" "1" "1" "0")
(command "_insert" "blkuc16" "5120,899.63" "1" "1" "180")
(command "_insert" "blkuc16" "5120,900.37" "1" "1" "0")
(command "_insert" "blkuc16" "5120,900" "1" "1" "180")
(command "_insert" "blkuc16" "5120,900.74" "1" "1" "0")
(command "_insert" "blkuc16" "5120,900.37" "1" "1" "180")
(command "_insert" "blkuc16" "5120,901.11" "1" "1" "0")
(command "_insert" "blkuc16" "5120,900.74" "1" "1" "180")
(command "_insert" "blkuc16" "5120,901.48" "1" "1" "0")
(command "_insert" "blkuc16" "5120,901.11" "1" "1" "180")
(command "_insert" "blkuc16" "5120,901.85" "1" "1" "0")
(command "_insert" "blkuc16" "5120,901.48" "1" "1" "180")
(command "_insert" "blkuc16" "5120,902.22" "1" "1" "0")
(command "_insert" "blkuc16" "5120,901.85" "1" "1" "180")
(command "_insert" "blkuc16" "5120,902.59" "1" "1" "0")
(command "_insert" "blkuc16" "5120,902.22" "1" "1" "180")
(command "_insert" "blkuc16" "5120,902.96" "1" "1" "0")
(command "_insert" "blkuc16" "5120,902.59" "1" "1" "180")
(command "_insert" "blkuc16" "5120,903.33" "1" "1" "0")
(command "_insert" "blkuc16" "5120,902.96" "1" "1" "180")
(command "_insert" "blkuc16" "5120,903.7" "1" "1" "0")
(command "_insert" "blkuc16" "5120,903.33" "1" "1" "180")
(command "_insert" "blkuc16" "5120,904.07" "1" "1" "0")
(command "_insert" "blkuc16" "5120,903.7" "1" "1" "180")
(command "_insert" "blkuc16" "5120,904.44" "1" "1" "0")
(command "_insert" "blkuc16" "5120,904.07" "1" "1" "180")
(command "_insert" "blkuc16" "5120,904.81" "1" "1" "0")
(command "_insert" "blkuc16" "5120,904.44" "1" "1" "180")
(command "_insert" "blkuc16" "5120,905.18" "1" "1" "0")
(command "_insert" "blkuc16" "5120,904.81" "1" "1" "180")
(command "_insert" "blkuc16" "5120,905.55" "1" "1" "0")
(command "_insert" "blkuc16" "5120,905.18" "1" "1" "180")
(command "_insert" "blkuc16" "5120,905.92" "1" "1" "0")
(command "_insert" "blkuc16" "5120,905.55" "1" "1" "180")
(command "_insert" "blkuc16" "5120,906.29" "1" "1" "0")
(command "_insert" "blkuc16" "5120,905.92" "1" "1" "180")
(command "_insert" "blkuc16" "5120,906.66" "1" "1" "0")
(command "_insert" "blkuc16" "5120,906.29" "1" "1" "180")
(command "_insert" "blkuc16" "5120,907.03" "1" "1" "0")
(command "_insert" "blkuc16" "5120,906.66" "1" "1" "180")
(command "_insert" "blkuc16" "5120,907.4" "1" "1" "0")
(command "_insert" "blkuc16" "5120,907.03" "1" "1" "180")
(command "_insert" "blkuc16" "5120,907.77" "1" "1" "0")
(command "_insert" "blkuc16" "5120,907.4" "1" "1" "180")
(command "_insert" "blkuc16" "5120,908.14" "1" "1" "0")
(command "_insert" "blkuc16" "5120,907.77" "1" "1" "180")
(command "_insert" "blkuc16" "5120,908.51" "1" "1" "0")
(command "_insert" "blkuc16" "5120,908.14" "1" "1" "180")
(command "_insert" "blkuc16" "5120,908.88" "1" "1" "0")
(command "_insert" "blkuc16" "5120,908.51" "1" "1" "180")
(command "_insert" "blkuc16" "5120,909.25" "1" "1" "0")
(command "_insert" "blkuc16" "5120,908.88" "1" "1" "180")
(command "_insert" "blkuc16" "5120,909.62" "1" "1" "0")
(command "_insert" "blkuc16" "5120,909.25" "1" "1" "180")
(command "_insert" "blkuc16" "5120,909.99" "1" "1" "0")
(command "_insert" "blkuc16" "5120,909.62" "1" "1" "180")
(command "_insert" "blkuc16" "5120,910.36" "1" "1" "0")
(command "_insert" "blkuc16" "5120,909.99" "1" "1" "180")
(command "_insert" "blkuc16" "5120,910.73" "1" "1" "0")
(command "_insert" "blkuc16" "5120,910.36" "1" "1" "180")
(command "_insert" "blkuc16" "5120,911.1" "1" "1" "0")
(command "_insert" "blkuc16" "5120,910.73" "1" "1" "180")
(command "_insert" "blkuc16" "5120,911.47" "1" "1" "0")
(command "_insert" "blkuc16" "5120,911.1" "1" "1" "180")
(command "_insert" "blkuc16" "5120,911.84" "1" "1" "0")
(command "_insert" "blkuc16" "5120,911.47" "1" "1" "180")
(command "_insert" "blkuc16" "5120,912.21" "1" "1" "0")
(command "_insert" "blkuc16" "5120,911.84" "1" "1" "180")
(command "_insert" "blkuc16" "5120,912.58" "1" "1" "0")
(command "_insert" "blkuc16" "5120,912.21" "1" "1" "180")
(command "_insert" "blkuc16" "5120,912.95" "1" "1" "0")
(command "_insert" "blkuc16" "5120,912.58" "1" "1" "180")
(command "_insert" "blkuc16" "5120,913.32" "1" "1" "0")
(command "_insert" "blkuc16" "5120,912.95" "1" "1" "180")
(command "_insert" "blkuc16" "5120,913.69" "1" "1" "0")
(command "_insert" "blkuc16" "5120,913.32" "1" "1" "180")
(command "_insert" "blkuc16" "5120,914.06" "1" "1" "0")
(command "_insert" "blkuc16" "5120,913.69" "1" "1" "180")
(command "_insert" "blkuc16" "5120,914.43" "1" "1" "0")
(command "_insert" "blkuc16" "5120,914.06" "1" "1" "180")
(command "_insert" "blkuc16" "5120,914.8" "1" "1" "0")
(command "_insert" "blkuc16" "5120,914.43" "1" "1" "180")
(command "_insert" "blkuc16" "5120,915.17" "1" "1" "0")
(command "_insert" "blkuc16" "5120,914.8" "1" "1" "180")
(command "_insert" "blkuc16" "5120,915.54" "1" "1" "0")
(command "_insert" "blkuc16" "5120,915.17" "1" "1" "180")
(command "_insert" "blkuc16" "5120,915.91" "1" "1" "0")
(command "_insert" "blkuc16" "5120,915.54" "1" "1" "180")
(command "_insert" "blkuc16" "5120,916.28" "1" "1" "0")
(command "_insert" "blkuc16" "5120,915.91" "1" "1" "180")
(command "_insert" "blkuc16" "5120,916.65" "1" "1" "0")
(command "_insert" "blkuc16" "5120,916.28" "1" "1" "180")
(command "_insert" "blkuc16" "5120,917.02" "1" "1" "0")
(command "_insert" "blkuc16" "5120,916.65" "1" "1" "180")
(command "_insert" "blkuc16" "5120,917.39" "1" "1" "0")
(command "_insert" "blkuc16" "5120,917.02" "1" "1" "180")
(command "_insert" "blkuc16" "5120,917.76" "1" "1" "0")
(command "_insert" "blkuc16" "5120,917.39" "1" "1" "180")
(command "_insert" "blkuc16" "5120,918.13" "1" "1" "0")
(command "_insert" "blkuc16" "5120,917.76" "1" "1" "180")
(command "_insert" "blkuc16" "5120,918.5" "1" "1" "0")
(command "_insert" "blkuc16" "5120,918.13" "1" "1" "180")
(command "_insert" "blkuc16" "5120,918.87" "1" "1" "0")
(command "_insert" "blkuc16" "5120,918.5" "1" "1" "180")
(command "_insert" "blkuc16" "5120,919.24" "1" "1" "0")
(command "_insert" "blkuc16" "5120,918.87" "1" "1" "180")
(command "_insert" "blkuc16" "5120,919.61" "1" "1" "0")
(command "_insert" "blkuc16" "5120,919.24" "1" "1" "180")
(command "_insert" "blkuc16" "5120,919.98" "1" "1" "0")
(command "_insert" "blkuc16" "5120,919.61" "1" "1" "180")
(command "_insert" "blkuc16" "5120,920.35" "1" "1" "0")
(command "_insert" "blkuc16" "5120,919.98" "1" "1" "180")
(command "_insert" "blkuc16" "5120,920.72" "1" "1" "0")
(command "_insert" "blkuc16" "5120,920.35" "1" "1" "180")
(command "_insert" "blkuc16" "5120,921.09" "1" "1" "0")
(command "_insert" "blkuc16" "5120,920.72" "1" "1" "180")
(command "_insert" "blkuc16" "5120,921.46" "1" "1" "0")
(command "_insert" "blkuc16" "5120,921.09" "1" "1" "180")
(command "_insert" "blkuc16" "5120,921.83" "1" "1" "0")
(command "_insert" "blkuc16" "5120,921.46" "1" "1" "180")
(command "_insert" "blkuc16" "5120,922.2" "1" "1" "0")
(command "_insert" "blkuc16" "5120,921.83" "1" "1" "180")
(command "_insert" "blkuc16" "5120,922.57" "1" "1" "0")
(command "_insert" "blkuc16" "5120,922.2" "1" "1" "180")
(command "_insert" "blkuc16" "5120,922.94" "1" "1" "0")
(command "_insert" "blkuc16" "5120,922.57" "1" "1" "180")
(command "_insert" "blkuc16" "5120,923.31" "1" "1" "0")
(command "_insert" "blkuc16" "5120,922.94" "1" "1" "180")
(command "_insert" "blkuc16" "5120,923.68" "1" "1" "0")
(command "_insert" "blkuc16" "5120,923.31" "1" "1" "180")
(command "_insert" "blkuc16" "5120,924.05" "1" "1" "0")
(command "_insert" "blkuc16" "5120,923.68" "1" "1" "180")
(command "_insert" "blkuc16" "5120,924.42" "1" "1" "0")
(command "_insert" "blkuc16" "5120,924.05" "1" "1" "180")
(command "_insert" "blkuc16" "5120,924.79" "1" "1" "0")
(command "_insert" "blkuc16" "5120,924.42" "1" "1" "180")
(command "_insert" "blkuc16" "5120,925.16" "1" "1" "0")
(command "_insert" "blkuc16" "5120,924.79" "1" "1" "180")
(command "_insert" "blkuc16" "5120,925.53" "1" "1" "0")
(command "_insert" "blkuc16" "5120,925.16" "1" "1" "180")
(command "_insert" "blkuc16" "5120,925.9" "1" "1" "0")
(command "_insert" "blkuc16" "5120,925.53" "1" "1" "180")
(command "_insert" "blkuc16" "5120,926.27" "1" "1" "0")
(command "_insert" "blkuc16" "5120,925.9" "1" "1" "180")
(command "_insert" "blkuc16" "5120,926.64" "1" "1" "0")
(command "_insert" "blkuc16" "5120,926.27" "1" "1" "180")
(command "_insert" "blkuc16" "5120,927.01" "1" "1" "0")
(command "_insert" "blkuc16" "5120,926.64" "1" "1" "180")
(command "_insert" "blkuc16" "5120,927.38" "1" "1" "0")
(command "_insert" "blkuc16" "5120,927.01" "1" "1" "180")
(command "_insert" "blkuc16" "5120,927.75" "1" "1" "0")
(command "_insert" "blkuc16" "5120,927.38" "1" "1" "180")
(command "_layer" "set" "phccover" "")
(command "_rectangle" "5118.858,933.3" "5121.142,866.7")
(command "_layer" "set" "nitride" "")
(setq phc16 currobj)
(command "_layer" "set" "cover" "")
(command "_rectangle" "5118.858,836.7" "5121.142,963.3")
(command "_layer" "set" "nitride" "")
(command "_layer" "set" "text" "")
(command "_circle" "5117.908,846.7" "0.075")
(command "_circle" "5117.533,846.7" "0.15")
(command "_circle" "5117.158,846.7" "0.075")
(command "_circle" "5116.783,846.7" "0.15")
(command "_circle" "5117.908,848.7" "0.075")
(command "_circle" "5117.533,848.7" "0.075")
(command "_circle" "5117.158,848.7" "0.15")
(command "_circle" "5116.783,848.7" "0.15")
(command "_circle" "5117.908,850.7" "0.075")
(command "_circle" "5117.533,850.7" "0.15")
(command "_circle" "5117.158,850.7" "0.15")
(command "_circle" "5116.783,850.7" "0.15")
(command "_circle" "5117.908,852.7" "0.075")
(command "_circle" "5117.533,852.7" "0.075")
(command "_circle" "5117.158,852.7" "0.075")
(command "_circle" "5116.783,852.7" "0.075")
(command "_circle" "5116.408,852.7" "0.15")
(command "_circle" "5117.908,854.7" "0.075")
(command "_circle" "5117.533,854.7" "0.15")
(command "_circle" "5117.158,854.7" "0.075")
(command "_circle" "5116.783,854.7" "0.075")
(command "_circle" "5116.408,854.7" "0.15")
(command "_circle" "5117.908,856.7" "0.075")
(command "_circle" "5117.533,856.7" "0.075")
(command "_circle" "5117.158,856.7" "0.15")
(command "_circle" "5116.783,856.7" "0.075")
(command "_circle" "5116.408,856.7" "0.15")
(command "_circle" "5117.908,858.7" "0.075")
(command "_circle" "5117.533,858.7" "0.15")
(command "_circle" "5117.158,858.7" "0.15")
(command "_circle" "5116.783,858.7" "0.075")
(command "_circle" "5116.408,858.7" "0.15")
(command "_circle" "5117.908,860.7" "0.075")
(command "_circle" "5117.533,860.7" "0.075")
(command "_circle" "5117.158,860.7" "0.075")
(command "_circle" "5116.783,860.7" "0.15")
(command "_circle" "5116.408,860.7" "0.15")
(command "_circle" "5117.908,862.7" "0.075")
(command "_circle" "5117.533,862.7" "0.15")
(command "_circle" "5117.158,862.7" "0.075")
(command "_circle" "5116.783,862.7" "0.15")
(command "_circle" "5116.408,862.7" "0.15")
(command "_circle" "5117.908,864.7" "0.075")
(command "_circle" "5117.533,864.7" "0.075")
(command "_circle" "5117.158,864.7" "0.15")
(command "_circle" "5116.783,864.7" "0.15")
(command "_circle" "5116.408,864.7" "0.15")
(command "_circle" "5117.908,866.7" "0.075")
(command "_circle" "5117.533,866.7" "0.15")
(command "_circle" "5117.158,866.7" "0.15")
(command "_circle" "5116.783,866.7" "0.15")
(command "_circle" "5116.408,866.7" "0.15")
(command "_circle" "5117.908,868.7" "0.075")
(command "_circle" "5117.533,868.7" "0.075")
(command "_circle" "5117.158,868.7" "0.075")
(command "_circle" "5116.783,868.7" "0.075")
(command "_circle" "5116.408,868.7" "0.075")
(command "_circle" "5116.033,868.7" "0.15")
(command "_circle" "5117.908,870.7" "0.075")
(command "_circle" "5117.533,870.7" "0.15")
(command "_circle" "5117.158,870.7" "0.075")
(command "_circle" "5116.783,870.7" "0.075")
(command "_circle" "5116.408,870.7" "0.075")
(command "_circle" "5116.033,870.7" "0.15")
(command "_circle" "5117.908,872.7" "0.075")
(command "_circle" "5117.533,872.7" "0.075")
(command "_circle" "5117.158,872.7" "0.15")
(command "_circle" "5116.783,872.7" "0.075")
(command "_circle" "5116.408,872.7" "0.075")
(command "_circle" "5116.033,872.7" "0.15")
(command "_circle" "5117.908,874.7" "0.075")
(command "_circle" "5117.533,874.7" "0.15")
(command "_circle" "5117.158,874.7" "0.15")
(command "_circle" "5116.783,874.7" "0.075")
(command "_circle" "5116.408,874.7" "0.075")
(command "_circle" "5116.033,874.7" "0.15")
(command "_circle" "5117.908,876.7" "0.075")
(command "_circle" "5117.533,876.7" "0.075")
(command "_circle" "5117.158,876.7" "0.075")
(command "_circle" "5116.783,876.7" "0.15")
(command "_circle" "5116.408,876.7" "0.075")
(command "_circle" "5116.033,876.7" "0.15")
(command "_circle" "5117.908,878.7" "0.075")
(command "_circle" "5117.533,878.7" "0.15")
(command "_circle" "5117.158,878.7" "0.075")
(command "_circle" "5116.783,878.7" "0.15")
(command "_circle" "5116.408,878.7" "0.075")
(command "_circle" "5116.033,878.7" "0.15")
(command "_circle" "5117.908,880.7" "0.075")
(command "_circle" "5117.533,880.7" "0.075")
(command "_circle" "5117.158,880.7" "0.15")
(command "_circle" "5116.783,880.7" "0.15")
(command "_circle" "5116.408,880.7" "0.075")
(command "_circle" "5116.033,880.7" "0.15")
(command "_circle" "5117.908,882.7" "0.075")
(command "_circle" "5117.533,882.7" "0.15")
(command "_circle" "5117.158,882.7" "0.15")
(command "_circle" "5116.783,882.7" "0.15")
(command "_circle" "5116.408,882.7" "0.075")
(command "_circle" "5116.033,882.7" "0.15")
(command "_circle" "5117.908,884.7" "0.075")
(command "_circle" "5117.533,884.7" "0.075")
(command "_circle" "5117.158,884.7" "0.075")
(command "_circle" "5116.783,884.7" "0.075")
(command "_circle" "5116.408,884.7" "0.15")
(command "_circle" "5116.033,884.7" "0.15")
(command "_circle" "5117.908,886.7" "0.075")
(command "_circle" "5117.533,886.7" "0.15")
(command "_circle" "5117.158,886.7" "0.075")
(command "_circle" "5116.783,886.7" "0.075")
(command "_circle" "5116.408,886.7" "0.15")
(command "_circle" "5116.033,886.7" "0.15")
(command "_circle" "5117.908,888.7" "0.075")
(command "_circle" "5117.533,888.7" "0.075")
(command "_circle" "5117.158,888.7" "0.15")
(command "_circle" "5116.783,888.7" "0.075")
(command "_circle" "5116.408,888.7" "0.15")
(command "_circle" "5116.033,888.7" "0.15")
(command "_circle" "5117.908,890.7" "0.075")
(command "_circle" "5117.533,890.7" "0.15")
(command "_circle" "5117.158,890.7" "0.15")
(command "_circle" "5116.783,890.7" "0.075")
(command "_circle" "5116.408,890.7" "0.15")
(command "_circle" "5116.033,890.7" "0.15")
(command "_circle" "5117.908,892.7" "0.075")
(command "_circle" "5117.533,892.7" "0.075")
(command "_circle" "5117.158,892.7" "0.075")
(command "_circle" "5116.783,892.7" "0.15")
(command "_circle" "5116.408,892.7" "0.15")
(command "_circle" "5116.033,892.7" "0.15")
(command "_circle" "5117.908,894.7" "0.075")
(command "_circle" "5117.533,894.7" "0.15")
(command "_circle" "5117.158,894.7" "0.075")
(command "_circle" "5116.783,894.7" "0.15")
(command "_circle" "5116.408,894.7" "0.15")
(command "_circle" "5116.033,894.7" "0.15")
(command "_circle" "5117.908,896.7" "0.075")
(command "_circle" "5117.533,896.7" "0.075")
(command "_circle" "5117.158,896.7" "0.15")
(command "_circle" "5116.783,896.7" "0.15")
(command "_circle" "5116.408,896.7" "0.15")
(command "_circle" "5116.033,896.7" "0.15")
(command "_circle" "5117.908,898.7" "0.075")
(command "_circle" "5117.533,898.7" "0.15")
(command "_circle" "5117.158,898.7" "0.15")
(command "_circle" "5116.783,898.7" "0.15")
(command "_circle" "5116.408,898.7" "0.15")
(command "_circle" "5116.033,898.7" "0.15")
(command "_circle" "5117.908,900.7" "0.075")
(command "_circle" "5117.533,900.7" "0.075")
(command "_circle" "5117.158,900.7" "0.075")
(command "_circle" "5116.783,900.7" "0.075")
(command "_circle" "5116.408,900.7" "0.075")
(command "_circle" "5116.033,900.7" "0.075")
(command "_circle" "5115.658,900.7" "0.15")
(command "_circle" "5117.908,902.7" "0.075")
(command "_circle" "5117.533,902.7" "0.15")
(command "_circle" "5117.158,902.7" "0.075")
(command "_circle" "5116.783,902.7" "0.075")
(command "_circle" "5116.408,902.7" "0.075")
(command "_circle" "5116.033,902.7" "0.075")
(command "_circle" "5115.658,902.7" "0.15")
(command "_circle" "5117.908,904.7" "0.075")
(command "_circle" "5117.533,904.7" "0.075")
(command "_circle" "5117.158,904.7" "0.15")
(command "_circle" "5116.783,904.7" "0.075")
(command "_circle" "5116.408,904.7" "0.075")
(command "_circle" "5116.033,904.7" "0.075")
(command "_circle" "5115.658,904.7" "0.15")
(command "_circle" "5117.908,906.7" "0.075")
(command "_circle" "5117.533,906.7" "0.15")
(command "_circle" "5117.158,906.7" "0.15")
(command "_circle" "5116.783,906.7" "0.075")
(command "_circle" "5116.408,906.7" "0.075")
(command "_circle" "5116.033,906.7" "0.075")
(command "_circle" "5115.658,906.7" "0.15")
(command "_circle" "5117.908,908.7" "0.075")
(command "_circle" "5117.533,908.7" "0.075")
(command "_circle" "5117.158,908.7" "0.075")
(command "_circle" "5116.783,908.7" "0.15")
(command "_circle" "5116.408,908.7" "0.075")
(command "_circle" "5116.033,908.7" "0.075")
(command "_circle" "5115.658,908.7" "0.15")
(command "_circle" "5117.908,910.7" "0.075")
(command "_circle" "5117.533,910.7" "0.15")
(command "_circle" "5117.158,910.7" "0.075")
(command "_circle" "5116.783,910.7" "0.15")
(command "_circle" "5116.408,910.7" "0.075")
(command "_circle" "5116.033,910.7" "0.075")
(command "_circle" "5115.658,910.7" "0.15")
(command "_circle" "5117.908,912.7" "0.075")
(command "_circle" "5117.533,912.7" "0.075")
(command "_circle" "5117.158,912.7" "0.15")
(command "_circle" "5116.783,912.7" "0.15")
(command "_circle" "5116.408,912.7" "0.075")
(command "_circle" "5116.033,912.7" "0.075")
(command "_circle" "5115.658,912.7" "0.15")
(command "_circle" "5117.908,914.7" "0.075")
(command "_circle" "5117.533,914.7" "0.15")
(command "_circle" "5117.158,914.7" "0.15")
(command "_circle" "5116.783,914.7" "0.15")
(command "_circle" "5116.408,914.7" "0.075")
(command "_circle" "5116.033,914.7" "0.075")
(command "_circle" "5115.658,914.7" "0.15")
(command "_circle" "5117.908,916.7" "0.075")
(command "_circle" "5117.533,916.7" "0.075")
(command "_circle" "5117.158,916.7" "0.075")
(command "_circle" "5116.783,916.7" "0.075")
(command "_circle" "5116.408,916.7" "0.15")
(command "_circle" "5116.033,916.7" "0.075")
(command "_circle" "5115.658,916.7" "0.15")
(command "_circle" "5117.908,918.7" "0.075")
(command "_circle" "5117.533,918.7" "0.15")
(command "_circle" "5117.158,918.7" "0.075")
(command "_circle" "5116.783,918.7" "0.075")
(command "_circle" "5116.408,918.7" "0.15")
(command "_circle" "5116.033,918.7" "0.075")
(command "_circle" "5115.658,918.7" "0.15")
(command "_circle" "5117.908,920.7" "0.075")
(command "_circle" "5117.533,920.7" "0.075")
(command "_circle" "5117.158,920.7" "0.15")
(command "_circle" "5116.783,920.7" "0.075")
(command "_circle" "5116.408,920.7" "0.15")
(command "_circle" "5116.033,920.7" "0.075")
(command "_circle" "5115.658,920.7" "0.15")
(command "_circle" "5117.908,922.7" "0.075")
(command "_circle" "5117.533,922.7" "0.15")
(command "_circle" "5117.158,922.7" "0.15")
(command "_circle" "5116.783,922.7" "0.075")
(command "_circle" "5116.408,922.7" "0.15")
(command "_circle" "5116.033,922.7" "0.075")
(command "_circle" "5115.658,922.7" "0.15")
(command "_circle" "5117.908,924.7" "0.075")
(command "_circle" "5117.533,924.7" "0.075")
(command "_circle" "5117.158,924.7" "0.075")
(command "_circle" "5116.783,924.7" "0.15")
(command "_circle" "5116.408,924.7" "0.15")
(command "_circle" "5116.033,924.7" "0.075")
(command "_circle" "5115.658,924.7" "0.15")
(command "_circle" "5117.908,926.7" "0.075")
(command "_circle" "5117.533,926.7" "0.15")
(command "_circle" "5117.158,926.7" "0.075")
(command "_circle" "5116.783,926.7" "0.15")
(command "_circle" "5116.408,926.7" "0.15")
(command "_circle" "5116.033,926.7" "0.075")
(command "_circle" "5115.658,926.7" "0.15")
(command "_circle" "5117.908,928.7" "0.075")
(command "_circle" "5117.533,928.7" "0.075")
(command "_circle" "5117.158,928.7" "0.15")
(command "_circle" "5116.783,928.7" "0.15")
(command "_circle" "5116.408,928.7" "0.15")
(command "_circle" "5116.033,928.7" "0.075")
(command "_circle" "5115.658,928.7" "0.15")
(command "_circle" "5117.908,930.7" "0.075")
(command "_circle" "5117.533,930.7" "0.15")
(command "_circle" "5117.158,930.7" "0.15")
(command "_circle" "5116.783,930.7" "0.15")
(command "_circle" "5116.408,930.7" "0.15")
(command "_circle" "5116.033,930.7" "0.075")
(command "_circle" "5115.658,930.7" "0.15")
(command "_circle" "5117.908,932.7" "0.075")
(command "_circle" "5117.533,932.7" "0.075")
(command "_circle" "5117.158,932.7" "0.075")
(command "_circle" "5116.783,932.7" "0.075")
(command "_circle" "5116.408,932.7" "0.075")
(command "_circle" "5116.033,932.7" "0.15")
(command "_circle" "5115.658,932.7" "0.15")
(command "_circle" "5117.908,934.7" "0.075")
(command "_circle" "5117.533,934.7" "0.15")
(command "_circle" "5117.158,934.7" "0.075")
(command "_circle" "5116.783,934.7" "0.075")
(command "_circle" "5116.408,934.7" "0.075")
(command "_circle" "5116.033,934.7" "0.15")
(command "_circle" "5115.658,934.7" "0.15")
(command "_circle" "5117.908,936.7" "0.075")
(command "_circle" "5117.533,936.7" "0.075")
(command "_circle" "5117.158,936.7" "0.15")
(command "_circle" "5116.783,936.7" "0.075")
(command "_circle" "5116.408,936.7" "0.075")
(command "_circle" "5116.033,936.7" "0.15")
(command "_circle" "5115.658,936.7" "0.15")
(command "_circle" "5117.908,938.7" "0.075")
(command "_circle" "5117.533,938.7" "0.15")
(command "_circle" "5117.158,938.7" "0.15")
(command "_circle" "5116.783,938.7" "0.075")
(command "_circle" "5116.408,938.7" "0.075")
(command "_circle" "5116.033,938.7" "0.15")
(command "_circle" "5115.658,938.7" "0.15")
(command "_circle" "5117.908,940.7" "0.075")
(command "_circle" "5117.533,940.7" "0.075")
(command "_circle" "5117.158,940.7" "0.075")
(command "_circle" "5116.783,940.7" "0.15")
(command "_circle" "5116.408,940.7" "0.075")
(command "_circle" "5116.033,940.7" "0.15")
(command "_circle" "5115.658,940.7" "0.15")
(command "_circle" "5117.908,942.7" "0.075")
(command "_circle" "5117.533,942.7" "0.15")
(command "_circle" "5117.158,942.7" "0.075")
(command "_circle" "5116.783,942.7" "0.15")
(command "_circle" "5116.408,942.7" "0.075")
(command "_circle" "5116.033,942.7" "0.15")
(command "_circle" "5115.658,942.7" "0.15")
(command "_circle" "5117.908,944.7" "0.075")
(command "_circle" "5117.533,944.7" "0.075")
(command "_circle" "5117.158,944.7" "0.15")
(command "_circle" "5116.783,944.7" "0.15")
(command "_circle" "5116.408,944.7" "0.075")
(command "_circle" "5116.033,944.7" "0.15")
(command "_circle" "5115.658,944.7" "0.15")
(command "_circle" "5117.908,946.7" "0.075")
(command "_circle" "5117.533,946.7" "0.15")
(command "_circle" "5117.158,946.7" "0.15")
(command "_circle" "5116.783,946.7" "0.15")
(command "_circle" "5116.408,946.7" "0.075")
(command "_circle" "5116.033,946.7" "0.15")
(command "_circle" "5115.658,946.7" "0.15")
(command "_circle" "5117.908,948.7" "0.075")
(command "_circle" "5117.533,948.7" "0.075")
(command "_circle" "5117.158,948.7" "0.075")
(command "_circle" "5116.783,948.7" "0.075")
(command "_circle" "5116.408,948.7" "0.15")
(command "_circle" "5116.033,948.7" "0.15")
(command "_circle" "5115.658,948.7" "0.15")
(command "_circle" "5117.908,950.7" "0.075")
(command "_circle" "5117.533,950.7" "0.15")
(command "_circle" "5117.158,950.7" "0.075")
(command "_circle" "5116.783,950.7" "0.075")
(command "_circle" "5116.408,950.7" "0.15")
(command "_circle" "5116.033,950.7" "0.15")
(command "_circle" "5115.658,950.7" "0.15")
(command "_circle" "5117.908,952.7" "0.075")
(command "_circle" "5117.533,952.7" "0.075")
(command "_circle" "5117.158,952.7" "0.15")
(command "_circle" "5116.783,952.7" "0.075")
(command "_circle" "5116.408,952.7" "0.15")
(command "_circle" "5116.033,952.7" "0.15")
(command "_circle" "5115.658,952.7" "0.15")
(command "_circle" "5117.908,954.7" "0.075")
(command "_circle" "5117.533,954.7" "0.15")
(command "_circle" "5117.158,954.7" "0.15")
(command "_circle" "5116.783,954.7" "0.075")
(command "_circle" "5116.408,954.7" "0.15")
(command "_circle" "5116.033,954.7" "0.15")
(command "_circle" "5115.658,954.7" "0.15")
(command "_circle" "5117.908,956.7" "0.075")
(command "_circle" "5117.533,956.7" "0.075")
(command "_circle" "5117.158,956.7" "0.075")
(command "_circle" "5116.783,956.7" "0.15")
(command "_circle" "5116.408,956.7" "0.15")
(command "_circle" "5116.033,956.7" "0.15")
(command "_circle" "5115.658,956.7" "0.15")
(command "_circle" "5117.908,958.7" "0.075")
(command "_circle" "5117.533,958.7" "0.15")
(command "_circle" "5117.158,958.7" "0.075")
(command "_circle" "5116.783,958.7" "0.15")
(command "_circle" "5116.408,958.7" "0.15")
(command "_circle" "5116.033,958.7" "0.15")
(command "_circle" "5115.658,958.7" "0.15")
(command "_circle" "5117.908,960.7" "0.075")
(command "_circle" "5117.533,960.7" "0.075")
(command "_circle" "5117.158,960.7" "0.15")
(command "_circle" "5116.783,960.7" "0.15")
(command "_circle" "5116.408,960.7" "0.15")
(command "_circle" "5116.033,960.7" "0.15")
(command "_circle" "5115.658,960.7" "0.15")
(command "_circle" "5117.908,962.7" "0.075")
(command "_circle" "5117.533,962.7" "0.15")
(command "_circle" "5117.158,962.7" "0.15")
(command "_circle" "5116.783,962.7" "0.15")
(command "_circle" "5116.408,962.7" "0.15")
(command "_circle" "5116.033,962.7" "0.15")
(command "_circle" "5115.658,962.7" "0.15")
(command "_layer" "set" "nitride" "")
(command "_layer" "set" "text" "")
(command-s "_text" "5106.858,963.3" "2" "-90" "a = 370 nm" )
(sssetfirst nil (ssget "_L"))
(if (not (numberp (vl-string-search "Mac" (getvar "platform")))) (c:txtexp))
(command "_layer" "set" "nitride" "")
(command "_layer" "set" "text" "")
(command-s "_text" "5103.858,963.3" "2" "-90" "gap = 250 nm" )
(sssetfirst nil (ssget "_L"))
(if (not (numberp (vl-string-search "Mac" (getvar "platform")))) (c:txtexp))
(command "_layer" "set" "nitride" "")
(command "_layer" "set" "text" "")
(command-s "_text" "5100.858,963.3" "2" "-90" "amplitude = 142 nm" )
(sssetfirst nil (ssget "_L"))
(if (not (numberp (vl-string-search "Mac" (getvar "platform")))) (c:txtexp))
(command "_layer" "set" "nitride" "")
(command "_layer" "set" "text" "")
(command-s "_text" "5097.858,963.3" "2" "-90" "start width = 280 nm" )
(sssetfirst nil (ssget "_L"))
(if (not (numberp (vl-string-search "Mac" (getvar "platform")))) (c:txtexp))
(command "_layer" "set" "nitride" "")
(command "_layer" "set" "text" "")
(command-s "_text" "5094.858,963.3" "2" "-90" "width = 304 nm" )
(sssetfirst nil (ssget "_L"))
(if (not (numberp (vl-string-search "Mac" (getvar "platform")))) (c:txtexp))
(command "_layer" "set" "nitride" "")
(command "_layer" "set" "text" "")
(command-s "_text" "5091.858,963.3" "2" "-90" "taper: 15" )
(sssetfirst nil (ssget "_L"))
(if (not (numberp (vl-string-search "Mac" (getvar "platform")))) (c:txtexp))
(command "_layer" "set" "nitride" "")
(command "_layer" "set" "text" "")
(command-s "_text" "5088.858,963.3" "2" "-90" "nominal: 150" )
(sssetfirst nil (ssget "_L"))
(if (not (numberp (vl-string-search "Mac" (getvar "platform")))) (c:txtexp))
(command "_layer" "set" "nitride" "")
(command "_layer" "set" "indicators" "")
(setq coords (list 
(list 5040.415 940) 
(list 5040.415 920) 
(list 5020.415 900) 
(list 5040.415 880) 
(list 5040.415 860) 
(list 5040.415 900) 
(list 5040.415 887.0711) 
(list 5027.4861 900) 
(list 5040.415 912.9289) 
(list 5040.415 900)))
(apply 'command (append '("pline") coords '("c")))
(command "._fillet" "radius" "1" "._fillet" "P" (entlast))
(setq coords (list 
(list 5199.585 940) 
(list 5199.585 920) 
(list 5219.585 900) 
(list 5199.585 880) 
(list 5199.585 860) 
(list 5199.585 900) 
(list 5199.585 887.0711) 
(list 5212.5139 900) 
(list 5199.585 912.9289) 
(list 5199.585 900)))
(apply 'command (append '("pline") coords '("c")))
(command "._fillet" "radius" "1" "._fillet" "P" (entlast))
(command "_layer" "set" "holes" "")
(command "_circle" "5038.0629,914.1124" "0.5")
(command "_circle" "5035.7109,911.7603" "0.5")
(command "_circle" "5033.3588,909.4083" "0.5")
(command "_circle" "5031.0067,907.0562" "0.5")
(command "_circle" "5028.6547,904.7041" "0.5")
(command "_circle" "5026.3026,902.3521" "0.5")
(command "_circle" "5023.9505,900" "0.5")
(command "_circle" "5026.3026,897.6479" "0.5")
(command "_circle" "5028.6547,895.2959" "0.5")
(command "_circle" "5031.0067,892.9438" "0.5")
(command "_circle" "5033.3588,890.5917" "0.5")
(command "_circle" "5035.7109,888.2397" "0.5")
(command "_circle" "5038.0629,885.8876" "0.5")
(command "_circle" "5201.9371,914.1124" "0.5")
(command "_circle" "5204.2891,911.7603" "0.5")
(command "_circle" "5206.6412,909.4083" "0.5")
(command "_circle" "5208.9933,907.0562" "0.5")
(command "_circle" "5211.3453,904.7041" "0.5")
(command "_circle" "5213.6974,902.3521" "0.5")
(command "_circle" "5216.0495,900" "0.5")
(command "_circle" "5213.6974,897.6479" "0.5")
(command "_circle" "5211.3453,895.2959" "0.5")
(command "_circle" "5208.9933,892.9438" "0.5")
(command "_circle" "5206.6412,890.5917" "0.5")
(command "_circle" "5204.2891,888.2397" "0.5")
(command "_circle" "5201.9371,885.8876" "0.5")
(command "_layer" "set" "nitride" "")
(command "_block" "blkcoupler16" "5120,900" coupler16 "")
(command "_insert" "blkcoupler16" "5120,900" "1" "1" "0")
(command "_insert" "blkcoupler16" "5120,900" "1" "1" "180")
(command "_block" "blksinglenanobeam16" "5120,900" singlenanobeam16 "")
(command "_insert" "blksinglenanobeam16" "5120,900" "1" "1" "0")
(command "_insert" "blksinglenanobeam16" "5120,900" "1" "1" "180")
(command "_block" "blkanglednodearray16" "5120,900" anglednodearray16 "")
(command "_insert" "blkanglednodearray16" "5120,900" "1" "1" "0")
(command "_insert" "blkanglednodearray16" "5120,900" "1" "1" "180")
(command "_block" "blkcooledsinglenanobeam16" "5120,900" cooledsinglenanobeam16 "")
(command "_insert" "blkcooledsinglenanobeam16" "5120,900" "1" "1" "0")
(command "_insert" "blkcooledsinglenanobeam16" "5120,900" "1" "1" "180")
(command "_block" "blkyjunction16" "5120,900" yjunction16 "")
(command "_insert" "blkyjunction16" "5120,900" "1" "1" "0")
(command "_insert" "blkyjunction16" "5120,900" "1" "1" "180")
; DRAWING BULGING VEE GROOVE
(command "_layer" "set" "vgroove" "")
(setq coords (list 
(list 5045.415 -605) 
(list 5045.415 0) 
(list 5045.415 0) 
(list 5045.415 1800) 
(list 5045.415 1800) 
(list 5045.415 2405) 
(list 5194.585 2405) 
(list 5194.585 1800) 
(list 5194.585 1800) 
(list 5194.585 0) 
(list 5194.585 0) 
(list 5194.585 -605)))
(apply 'command (append '("pline") coords '("c")))
(command "._fillet" "radius" "0" "._fillet" "P" (entlast))
(command "_layer" "set" "window" "")
(command "_rectangle" "5045.415,-1935" "5194.585,-600")
(command "_rectangle" "5045.415,2400" "5194.585,5300")
(command "_layer" "set" "grid" "")
(command "_rectangle" "5046.415,-1934" "5069.9433,-1909.2133")
(command "_array" "last" "" "R" "75" "3" "25.7867" "24.5283")
(command "_rectangle" "5121,-1934" "5144.5283,-1909.2133")
(command "_array" "last" "" "R" "75" "3" "25.7867" "24.5283")
(command "_rectangle" "5046.415,1" "5069.9433,25.7")
(command "_array" "last" "" "R" "70" "3" "25.7" "24.5283")
(command "_rectangle" "5121,1" "5144.5283,25.7")
(command "_array" "last" "" "R" "70" "3" "25.7" "24.5283")
(command "_rectangle" "5046.415,1801" "5069.9433,1825.9185")
(command "_array" "last" "" "R" "135" "3" "25.9185" "24.5283")
(command "_rectangle" "5121,1801" "5144.5283,1825.9185")
(command "_array" "last" "" "R" "135" "3" "25.9185" "24.5283")
(command "_layer" "set" "vgrooveFDA" "")
(command "_rectangle" "5194.585,-2233" "5045.415,-1933")
(command "_layer" "set" "nitride" "")
(command "_layer" "set" "holes" "")
(command "_circle" "5197.085,331.5" "0.5")
(command "_array" "last" "" "R" "379" "1" "3" "2.5")
(command "_circle" "5042.915,331.5" "0.5")
(command "_array" "last" "" "R" "379" "1" "3" "-2.5")
(command "_layer" "set" "nitride" "")
(command "_layer" "set" "window" "")
(command "_layer" "set" "window" "")
(command "_rectangle" "5199.585,0" "6426.225,1800")
(command "._fillet" "radius" "20" "._fillet" "P" (entlast))
(command "_layer" "set" "grid" "")
(command "_rectangle" "5200.585,1" "5225.1192,25.7")
(command "_array" "last" "" "R" "70" "48" "25.7" "25.5342")
; DRAWING REGION LAYER
(command "_layer" "set" "regionLayer16" "")
(command "_rectangle" "5040,-460" "5200,2260")
(command "_layer" "set" "nitride" "")
(setq coupler16 nil)
(setq singlenanobeam16 nil)
(setq anglednodearray16 nil)
(setq cooledsinglenanobeam16 nil)
(setq yjunction16 nil)
(command "_layer" "set" "extent" "")
(command "_rectangle" "-2040,-2480" "-2020,-2460")
(command "_rectangle" "7940,-2480" "7960,-2460")
(command "_rectangle" "-2040,8500" "-2020,8520")
(command "_rectangle" "7940,8500" "7960,8520")
(command "_layer" "set" "marks" "")
(setq coords (list 
(list 0 -880) 
(list 90 -880) 
(list 90 -810) 
(list 70 -810) 
(list 70 -790) 
(list 90 -790) 
(list 90 -880) 
(list 160 -880) 
(list 160 -720) 
(list 0 -720)))
(apply 'command (append '("pline") coords '("c")))
(setq coords (list 
(list 5760 -880) 
(list 5850 -880) 
(list 5850 -810) 
(list 5830 -810) 
(list 5830 -790) 
(list 5850 -790) 
(list 5850 -880) 
(list 5920 -880) 
(list 5920 -720) 
(list 5760 -720)))
(apply 'command (append '("pline") coords '("c")))
(setq coords (list 
(list 0 2640) 
(list 90 2640) 
(list 90 2710) 
(list 70 2710) 
(list 70 2730) 
(list 90 2730) 
(list 90 2640) 
(list 160 2640) 
(list 160 2800) 
(list 0 2800)))
(apply 'command (append '("pline") coords '("c")))
(setq coords (list 
(list 5760 2640) 
(list 5850 2640) 
(list 5850 2710) 
(list 5830 2710) 
(list 5830 2730) 
(list 5850 2730) 
(list 5850 2640) 
(list 5920 2640) 
(list 5920 2800) 
(list 5760 2800)))
(apply 'command (append '("pline") coords '("c")))
(command "_layer" "set" "marks" "")
(command "_rectangle" "70,-330" "90,-310")
(command "_rectangle" "5830,-330" "5850,-310")
(command "_rectangle" "70,2230" "90,2250")
(command "_rectangle" "5830,2230" "5850,2250")
(command "_layer" "set" "nitride" "")
(command "_zoom" "extents")
; DRAW LAYERS, SET COLORS
(command "_layer" "OFF" "grid" "")
(command "_saveas" "DXF" "Version" "2000" "" "/Users/Andrew/Documents/Repositories/fabrication/Writes/2016-05-26 Rugrats/dil16.dxf")
