(defun x-coords (input-coords) (mapcar '(lambda (x) (nth 0 x)) input-coords))
(defun y-coords (input-coords) (mapcar '(lambda (x) (nth 1 x)) input-coords))
(defun remove-nil (in) (apply 'append (mapcar '(lambda (x) (if (not (null x)) (list x) ) ) in) ))
(defun get-coords (input-entity) (remove-nil (mapcar '(lambda (x) (if (= (car x) 10) (cdr x))) input-entity)))
(defun c:zoom-named (entname) (command "_zoom" "object" entname "")(princ))
(if (not (numberp (vl-string-search "Mac" (getvar "platform")))) (load "TXTEXP.LSP"))
;; NUMBER OF LAYERS: 16
; ERASE ALL
(command "_erase" "all" "")
; DRAW LAYERS, SET COLORS
(command "_layer" "new" "negYjunc" "")
(command "_layer" "new" "nitride" "")
(command "_layer" "new" "slices" "")
(command "_layer" "new" "holes" "")
(command "_layer" "new" "vgroove" "")
(command "_layer" "new" "vgrooveFDA" "")
(command "_layer" "new" "window" "")
(command "_layer" "new" "marks" "")
(command "_layer" "new" "extent" "")
(command "_layer" "new" "cover" "")
(command "_layer" "new" "grid" "")
(command "_layer" "new" "pads" "")
(command "_layer" "new" "text" "")
(command "_layer" "new" "fda1" "")
(command "_layer" "new" "prebias" "")
(command "_layer" "new" "phc" "")
(command "_layer" "new" "phccover" "")
(command "_layer" "new" "tethers" "")
(command "_layer" "new" "indicators" "")
(command "_layer" "new" "regionLayer1" "")
(command "_layer" "new" "regionLayer2" "")
(command "_layer" "new" "regionLayer3" "")
(command "_layer" "new" "regionLayer4" "")
(command "_layer" "new" "regionLayer5" "")
(command "_layer" "new" "regionLayer6" "")
(command "_layer" "new" "regionLayer7" "")
(command "_layer" "new" "regionLayer8" "")
(command "_layer" "new" "regionLayer9" "")
(command "_layer" "new" "regionLayer10" "")
(command "_layer" "new" "regionLayer11" "")
(command "_layer" "new" "regionLayer12" "")
(command "_layer" "new" "regionLayer13" "")
(command "_layer" "new" "regionLayer14" "")
(command "_layer" "new" "regionLayer15" "")
(command "_layer" "new" "regionLayer16" "")
(command "_layer" "color" "green" "negYjunc" "")
(command "_layer" "color" "white" "nitride" "")
(command "_layer" "color" "red" "slices" "")
(command "_layer" "color" "blue" "holes" "")
(command "_layer" "color" "green" "vgroove" "")
(command "_layer" "color" "red" "vgrooveFDA" "")
(command "_layer" "color" "yellow" "window" "")
(command "_layer" "color" "yellow" "marks" "")
(command "_layer" "color" "yellow" "extent" "")
(command "_layer" "color" "yellow" "cover" "")
(command "_layer" "color" "176" "grid" "")
(command "_layer" "color" "red" "pads" "")
(command "_layer" "color" "white" "text" "")
(command "_layer" "color" "1" "fda1" "")
(command "_layer" "color" "6" "prebias" "")
(command "_layer" "color" "5" "phc" "")
(command "_layer" "set" "negYjunc" "")
(command "_zoom" (list -0.05 -0.05) (list 0.05 0.05))
(command "_purge" "B" "*" "N")
; DEVICE #1
(command "_layer" "set" "window" "")
(command "_circle" "232.915,-415" "5")
(command "_layer" "set" "nitride" "")
(setq currobj nil)
(setq currobj (ssadd))
; DRAWING COUPLER
(setq coords (list 
(list 320.0615 -415) 
(list 320.0615 -413) 
(list 393.585 -413) 
(list 393.585 -413) 
(list 393.9677 -413.0761) 
(list 394.2921 -413.2929) 
(list 394.5089 -413.6173) 
(list 394.585 -414) 
(list 394.585 -411.8) 
(list 394.585 -411.8) 
(list 394.5089 -412.1827) 
(list 394.2921 -412.5071) 
(list 393.9677 -412.7239) 
(list 393.585 -412.8) 
(list 320.0615 -412.8) 
(list 320.0615 -410.8) 
(list 319.9385 -410.8) 
(list 319.9385 -412.8) 
(list 246.415 -412.8) 
(list 246.0323 -412.7239) 
(list 245.7079 -412.5071) 
(list 245.4911 -412.1827) 
(list 245.415 -411.8) 
(list 245.415 -411.8) 
(list 245.415 -414) 
(list 245.4911 -413.6173) 
(list 245.7079 -413.2929) 
(list 246.0323 -413.0761) 
(list 246.415 -413) 
(list 246.415 -413) 
(list 319.9385 -413) 
(list 319.9385 -415)))
(apply 'command (append '("pline") coords '("c")))
(setq currobj (ssadd (entlast) currobj))
(command "._fillet" "radius" "0.3" "._fillet" "P" (entlast))
(command "_layer" "set" "holes" "")
(command "_circle" "320,-412.9" "0.113")
(setq currobj (ssadd (entlast) currobj))
(command "_layer" "set" "nitride" "")
(command "_layer" "set" "text" "")
(command "_circle" "319.2,-415" "0.075")
(command "_circle" "319.2,-414.7" "0.075")
(command "_circle" "319.2,-414.4" "0.075")
(command "_circle" "318.9,-415" "0.075")
(command "_circle" "318.9,-414.7" "0.075")
(command "_circle" "318.9,-414.4" "0.075")
(command "_circle" "318.6,-415" "0.075")
(command "_circle" "318.6,-414.7" "0.075")
(command "_circle" "318.6,-414.4" "0.075")
(command "_layer" "set" "nitride" "")
(command "_layer" "set" "prebias" "")
(command "_rectangle" "245.415,-414" "394.585,-411.8")
(setq currobj (ssadd (entlast) currobj))
(command "_rectangle" "319.9385,-415" "320.0615,-410.8")
(setq currobj (ssadd (entlast) currobj))
(command "_layer" "set" "nitride" "")
(setq coupler1 currobj)
(setq currobj nil)
(setq currobj (ssadd))
; DRAWING SINGLE NANOBEAM
(setq coords (list 
(list 320.0615 -410.8) 
(list 320.0615 -409.1417) 
(list 320.0615 -407.4833) 
(list 320.0615 -405.825) 
(list 320.0615 -404.1667) 
(list 320.0615 -402.5083) 
(list 320.0615 -400.85) 
(list 320.0615 -399.1917) 
(list 320.0615 -397.5333) 
(list 320.0616 -395.875) 
(list 320.0616 -394.2167) 
(list 320.0616 -392.5583) 
(list 320.0616 -390.9) 
(list 320.0617 -389.2417) 
(list 320.0617 -387.5833) 
(list 320.0617 -385.925) 
(list 320.0618 -384.2667) 
(list 320.0619 -382.6083) 
(list 320.0619 -380.95) 
(list 320.062 -379.2917) 
(list 320.0621 -377.6333) 
(list 320.0622 -375.975) 
(list 320.0623 -374.3167) 
(list 320.0624 -372.6583) 
(list 320.0625 -371) 
(list 320.0626 -369.3417) 
(list 320.0628 -367.6833) 
(list 320.0629 -366.025) 
(list 320.0631 -364.3667) 
(list 320.0632 -362.7083) 
(list 320.0634 -361.05) 
(list 320.0636 -359.3917) 
(list 320.0638 -357.7333) 
(list 320.0641 -356.075) 
(list 320.0643 -354.4167) 
(list 320.0646 -352.7583) 
(list 320.0648 -351.1) 
(list 320.0651 -349.4417) 
(list 320.0654 -347.7833) 
(list 320.0657 -346.125) 
(list 320.0661 -344.4667) 
(list 320.0664 -342.8083) 
(list 320.0668 -341.15) 
(list 320.0672 -339.4917) 
(list 320.0676 -337.8333) 
(list 320.068 -336.175) 
(list 320.0685 -334.5167) 
(list 320.0689 -332.8583) 
(list 320.0694 -331.2) 
(list 320.0699 -329.5417) 
(list 320.0704 -327.8833) 
(list 320.071 -326.225) 
(list 320.0715 -324.5667) 
(list 320.0721 -322.9083) 
(list 320.0728 -321.25) 
(list 320.0734 -319.5917) 
(list 320.0741 -317.9333) 
(list 320.0747 -316.275) 
(list 320.0754 -314.6167) 
(list 320.0762 -312.9583) 
(list 320.0769 -311.3) 
(list 320.0777 -309.6417) 
(list 320.0785 -307.9833) 
(list 320.0794 -306.325) 
(list 320.0802 -304.6667) 
(list 320.0811 -303.0083) 
(list 320.082 -301.35) 
(list 320.083 -299.6917) 
(list 320.084 -298.0333) 
(list 320.085 -296.375) 
(list 320.086 -294.7167) 
(list 320.0871 -293.0583) 
(list 320.0882 -291.4) 
(list 320.0893 -289.7417) 
(list 320.0905 -288.0833) 
(list 320.0917 -286.425) 
(list 320.0929 -284.7667) 
(list 320.0941 -283.1083) 
(list 320.0954 -281.45) 
(list 320.0967 -279.7917) 
(list 320.0981 -278.1333) 
(list 320.0995 -276.475) 
(list 320.1009 -274.8167) 
(list 320.1024 -273.1583) 
(list 320.1039 -271.5) 
(list 320.1054 -269.8417) 
(list 320.107 -268.1833) 
(list 320.1086 -266.525) 
(list 320.1102 -264.8667) 
(list 320.1119 -263.2083) 
(list 320.1136 -261.55) 
(list 320.1154 -259.8917) 
(list 320.1172 -258.2333) 
(list 320.119 -256.575) 
(list 320.1209 -254.9167) 
(list 320.1228 -253.2583) 
(list 320.1247 -251.6) 
(list 320.1267 -249.9417) 
(list 320.1288 -248.2833) 
(list 320.1308 -246.625) 
(list 320.133 -244.9667) 
(list 320.1351 -243.3083) 
(list 320.1373 -241.65) 
(list 320.1396 -239.9917) 
(list 320.1419 -238.3333) 
(list 320.1442 -236.675) 
(list 320.1466 -235.0167) 
(list 320.1491 -233.3583) 
(list 320.1515 -231.7) 
(list 320.1541 -230.0417) 
(list 320.1566 -228.3833) 
(list 320.1592 -226.725) 
(list 320.1619 -225.0667) 
(list 320.1646 -223.4083) 
(list 320.1674 -221.75) 
(list 320.1702 -220.0917) 
(list 320.1731 -218.4333) 
(list 320.176 -216.775) 
(list 320.1789 -215.1167) 
(list 320.1819 -213.4583) 
(list 320.185 -211.8) 
(list 319.815 -211.8) 
(list 319.8181 -213.4583) 
(list 319.8211 -215.1167) 
(list 319.824 -216.775) 
(list 319.8269 -218.4333) 
(list 319.8298 -220.0917) 
(list 319.8326 -221.75) 
(list 319.8354 -223.4083) 
(list 319.8381 -225.0667) 
(list 319.8408 -226.725) 
(list 319.8434 -228.3833) 
(list 319.8459 -230.0417) 
(list 319.8485 -231.7) 
(list 319.8509 -233.3583) 
(list 319.8534 -235.0167) 
(list 319.8558 -236.675) 
(list 319.8581 -238.3333) 
(list 319.8604 -239.9917) 
(list 319.8627 -241.65) 
(list 319.8649 -243.3083) 
(list 319.867 -244.9667) 
(list 319.8692 -246.625) 
(list 319.8712 -248.2833) 
(list 319.8733 -249.9417) 
(list 319.8753 -251.6) 
(list 319.8772 -253.2583) 
(list 319.8791 -254.9167) 
(list 319.881 -256.575) 
(list 319.8828 -258.2333) 
(list 319.8846 -259.8917) 
(list 319.8864 -261.55) 
(list 319.8881 -263.2083) 
(list 319.8898 -264.8667) 
(list 319.8914 -266.525) 
(list 319.893 -268.1833) 
(list 319.8946 -269.8417) 
(list 319.8961 -271.5) 
(list 319.8976 -273.1583) 
(list 319.8991 -274.8167) 
(list 319.9005 -276.475) 
(list 319.9019 -278.1333) 
(list 319.9033 -279.7917) 
(list 319.9046 -281.45) 
(list 319.9059 -283.1083) 
(list 319.9071 -284.7667) 
(list 319.9083 -286.425) 
(list 319.9095 -288.0833) 
(list 319.9107 -289.7417) 
(list 319.9118 -291.4) 
(list 319.9129 -293.0583) 
(list 319.914 -294.7167) 
(list 319.915 -296.375) 
(list 319.916 -298.0333) 
(list 319.917 -299.6917) 
(list 319.918 -301.35) 
(list 319.9189 -303.0083) 
(list 319.9198 -304.6667) 
(list 319.9206 -306.325) 
(list 319.9215 -307.9833) 
(list 319.9223 -309.6417) 
(list 319.9231 -311.3) 
(list 319.9238 -312.9583) 
(list 319.9246 -314.6167) 
(list 319.9253 -316.275) 
(list 319.9259 -317.9333) 
(list 319.9266 -319.5917) 
(list 319.9272 -321.25) 
(list 319.9279 -322.9083) 
(list 319.9285 -324.5667) 
(list 319.929 -326.225) 
(list 319.9296 -327.8833) 
(list 319.9301 -329.5417) 
(list 319.9306 -331.2) 
(list 319.9311 -332.8583) 
(list 319.9315 -334.5167) 
(list 319.932 -336.175) 
(list 319.9324 -337.8333) 
(list 319.9328 -339.4917) 
(list 319.9332 -341.15) 
(list 319.9336 -342.8083) 
(list 319.9339 -344.4667) 
(list 319.9343 -346.125) 
(list 319.9346 -347.7833) 
(list 319.9349 -349.4417) 
(list 319.9352 -351.1) 
(list 319.9354 -352.7583) 
(list 319.9357 -354.4167) 
(list 319.9359 -356.075) 
(list 319.9362 -357.7333) 
(list 319.9364 -359.3917) 
(list 319.9366 -361.05) 
(list 319.9368 -362.7083) 
(list 319.9369 -364.3667) 
(list 319.9371 -366.025) 
(list 319.9372 -367.6833) 
(list 319.9374 -369.3417) 
(list 319.9375 -371) 
(list 319.9376 -372.6583) 
(list 319.9377 -374.3167) 
(list 319.9378 -375.975) 
(list 319.9379 -377.6333) 
(list 319.938 -379.2917) 
(list 319.9381 -380.95) 
(list 319.9381 -382.6083) 
(list 319.9382 -384.2667) 
(list 319.9383 -385.925) 
(list 319.9383 -387.5833) 
(list 319.9383 -389.2417) 
(list 319.9384 -390.9) 
(list 319.9384 -392.5583) 
(list 319.9384 -394.2167) 
(list 319.9384 -395.875) 
(list 319.9385 -397.5333) 
(list 319.9385 -399.1917) 
(list 319.9385 -400.85) 
(list 319.9385 -402.5083) 
(list 319.9385 -404.1667) 
(list 319.9385 -405.825) 
(list 319.9385 -407.4833) 
(list 319.9385 -409.1417) 
(list 319.9385 -410.8)))
(apply 'command (append '("pline") coords '("c")))
(setq currobj (ssadd (entlast) currobj))
(command "_layer" "set" "prebias" "")
(command "_rectangle" "319.815,-410.8" "320.185,-211.8")
(setq currobj (ssadd (entlast) currobj))
(command "_layer" "set" "nitride" "")
(setq singlenanobeam1 currobj)
(setq currobj nil)
(setq currobj (ssadd))
; DRAWING NODE ARRAY
(setq coords (list 
(list 320.185 -211.8) 
(list 320.5625 -201.8) 
(list 320.5625 -201.8) 
(list 320.5625 -200.8) 
(list 394.585 -212.6864) 
(list 394.585 -207.7434) 
(list 320.5625 -197.357) 
(list 320.5625 -196.357) 
(list 320.5625 -196.357) 
(list 320.2625 -186.357) 
(list 319.7375 -186.357) 
(list 319.4375 -196.357) 
(list 319.4375 -196.357) 
(list 319.4375 -197.357) 
(list 245.415 -207.7434) 
(list 245.415 -212.6864) 
(list 319.4375 -200.8) 
(list 319.4375 -201.8) 
(list 319.4375 -201.8) 
(list 319.815 -211.8)))
(apply 'command (append '("pline") coords '("c")))
(setq currobj (ssadd (entlast) currobj))
(command "_layer" "set" "prebias" "")
(setq coords (list 
(list 319.4375 -212.6864) 
(list 319.4375 -200.8) 
(list 245.415 -212.6864) 
(list 245.415 -207.7434) 
(list 319.4375 -197.357) 
(list 319.4375 -186.357) 
(list 320.5625 -186.357) 
(list 320.5625 -197.357) 
(list 394.585 -207.7434) 
(list 394.585 -212.6864) 
(list 320.5625 -200.8) 
(list 320.5625 -212.6864)))
(apply 'command (append '("pline") coords '("c")))
(setq currobj (ssadd (entlast) currobj))
(command "_layer" "set" "nitride" "")
(command "_layer" "set" "fda1" "")
(setq coords (list 
(list 320.5625 -200.657) 
(list 394.585 -212.5434) 
(list 394.585 -212.3664) 
(list 320.5625 -200.58)))
(apply 'command (append '("pline") coords '("c")))
(setq currobj (ssadd (entlast) currobj))
(setq coords (list 
(list 320.5625 -200.437) 
(list 394.585 -212.2234) 
(list 394.585 -212.0464) 
(list 320.5625 -200.36)))
(apply 'command (append '("pline") coords '("c")))
(setq currobj (ssadd (entlast) currobj))
(setq coords (list 
(list 320.5625 -200.217) 
(list 394.585 -211.9034) 
(list 394.585 -211.7264) 
(list 320.5625 -200.14)))
(apply 'command (append '("pline") coords '("c")))
(setq currobj (ssadd (entlast) currobj))
(setq coords (list 
(list 320.5625 -199.997) 
(list 394.585 -211.5834) 
(list 394.585 -211.4064) 
(list 320.5625 -199.92)))
(apply 'command (append '("pline") coords '("c")))
(setq currobj (ssadd (entlast) currobj))
(setq coords (list 
(list 320.5625 -199.777) 
(list 394.585 -211.2634) 
(list 394.585 -211.0864) 
(list 320.5625 -199.7)))
(apply 'command (append '("pline") coords '("c")))
(setq currobj (ssadd (entlast) currobj))
(setq coords (list 
(list 320.5625 -199.557) 
(list 394.585 -210.9434) 
(list 394.585 -210.7664) 
(list 320.5625 -199.48)))
(apply 'command (append '("pline") coords '("c")))
(setq currobj (ssadd (entlast) currobj))
(setq coords (list 
(list 320.5625 -199.337) 
(list 394.585 -210.6234) 
(list 394.585 -210.4464) 
(list 320.5625 -199.26)))
(apply 'command (append '("pline") coords '("c")))
(setq currobj (ssadd (entlast) currobj))
(setq coords (list 
(list 320.5625 -199.117) 
(list 394.585 -210.3034) 
(list 394.585 -210.1264) 
(list 320.5625 -199.04)))
(apply 'command (append '("pline") coords '("c")))
(setq currobj (ssadd (entlast) currobj))
(setq coords (list 
(list 320.5625 -198.897) 
(list 394.585 -209.9834) 
(list 394.585 -209.8064) 
(list 320.5625 -198.82)))
(apply 'command (append '("pline") coords '("c")))
(setq currobj (ssadd (entlast) currobj))
(setq coords (list 
(list 320.5625 -198.677) 
(list 394.585 -209.6634) 
(list 394.585 -209.4864) 
(list 320.5625 -198.6)))
(apply 'command (append '("pline") coords '("c")))
(setq currobj (ssadd (entlast) currobj))
(setq coords (list 
(list 320.5625 -198.457) 
(list 394.585 -209.3434) 
(list 394.585 -209.1664) 
(list 320.5625 -198.38)))
(apply 'command (append '("pline") coords '("c")))
(setq currobj (ssadd (entlast) currobj))
(setq coords (list 
(list 320.5625 -198.237) 
(list 394.585 -209.0234) 
(list 394.585 -208.8464) 
(list 320.5625 -198.16)))
(apply 'command (append '("pline") coords '("c")))
(setq currobj (ssadd (entlast) currobj))
(setq coords (list 
(list 320.5625 -198.017) 
(list 394.585 -208.7034) 
(list 394.585 -208.5264) 
(list 320.5625 -197.94)))
(apply 'command (append '("pline") coords '("c")))
(setq currobj (ssadd (entlast) currobj))
(setq coords (list 
(list 320.5625 -197.797) 
(list 394.585 -208.3834) 
(list 394.585 -208.2064) 
(list 320.5625 -197.72)))
(apply 'command (append '("pline") coords '("c")))
(setq currobj (ssadd (entlast) currobj))
(setq coords (list 
(list 320.5625 -197.577) 
(list 394.585 -208.0634) 
(list 394.585 -207.8864) 
(list 320.5625 -197.5)))
(apply 'command (append '("pline") coords '("c")))
(setq currobj (ssadd (entlast) currobj))
(setq coords (list 
(list 319.4375 -197.5) 
(list 245.415 -207.8864) 
(list 245.415 -208.0634) 
(list 319.4375 -197.577)))
(apply 'command (append '("pline") coords '("c")))
(setq currobj (ssadd (entlast) currobj))
(setq coords (list 
(list 319.4375 -197.72) 
(list 245.415 -208.2064) 
(list 245.415 -208.3834) 
(list 319.4375 -197.797)))
(apply 'command (append '("pline") coords '("c")))
(setq currobj (ssadd (entlast) currobj))
(setq coords (list 
(list 319.4375 -197.94) 
(list 245.415 -208.5264) 
(list 245.415 -208.7034) 
(list 319.4375 -198.017)))
(apply 'command (append '("pline") coords '("c")))
(setq currobj (ssadd (entlast) currobj))
(setq coords (list 
(list 319.4375 -198.16) 
(list 245.415 -208.8464) 
(list 245.415 -209.0234) 
(list 319.4375 -198.237)))
(apply 'command (append '("pline") coords '("c")))
(setq currobj (ssadd (entlast) currobj))
(setq coords (list 
(list 319.4375 -198.38) 
(list 245.415 -209.1664) 
(list 245.415 -209.3434) 
(list 319.4375 -198.457)))
(apply 'command (append '("pline") coords '("c")))
(setq currobj (ssadd (entlast) currobj))
(setq coords (list 
(list 319.4375 -198.6) 
(list 245.415 -209.4864) 
(list 245.415 -209.6634) 
(list 319.4375 -198.677)))
(apply 'command (append '("pline") coords '("c")))
(setq currobj (ssadd (entlast) currobj))
(setq coords (list 
(list 319.4375 -198.82) 
(list 245.415 -209.8064) 
(list 245.415 -209.9834) 
(list 319.4375 -198.897)))
(apply 'command (append '("pline") coords '("c")))
(setq currobj (ssadd (entlast) currobj))
(setq coords (list 
(list 319.4375 -199.04) 
(list 245.415 -210.1264) 
(list 245.415 -210.3034) 
(list 319.4375 -199.117)))
(apply 'command (append '("pline") coords '("c")))
(setq currobj (ssadd (entlast) currobj))
(setq coords (list 
(list 319.4375 -199.26) 
(list 245.415 -210.4464) 
(list 245.415 -210.6234) 
(list 319.4375 -199.337)))
(apply 'command (append '("pline") coords '("c")))
(setq currobj (ssadd (entlast) currobj))
(setq coords (list 
(list 319.4375 -199.48) 
(list 245.415 -210.7664) 
(list 245.415 -210.9434) 
(list 319.4375 -199.557)))
(apply 'command (append '("pline") coords '("c")))
(setq currobj (ssadd (entlast) currobj))
(setq coords (list 
(list 319.4375 -199.7) 
(list 245.415 -211.0864) 
(list 245.415 -211.2634) 
(list 319.4375 -199.777)))
(apply 'command (append '("pline") coords '("c")))
(setq currobj (ssadd (entlast) currobj))
(setq coords (list 
(list 319.4375 -199.92) 
(list 245.415 -211.4064) 
(list 245.415 -211.5834) 
(list 319.4375 -199.997)))
(apply 'command (append '("pline") coords '("c")))
(setq currobj (ssadd (entlast) currobj))
(setq coords (list 
(list 319.4375 -200.14) 
(list 245.415 -211.7264) 
(list 245.415 -211.9034) 
(list 319.4375 -200.217)))
(apply 'command (append '("pline") coords '("c")))
(setq currobj (ssadd (entlast) currobj))
(setq coords (list 
(list 319.4375 -200.36) 
(list 245.415 -212.0464) 
(list 245.415 -212.2234) 
(list 319.4375 -200.437)))
(apply 'command (append '("pline") coords '("c")))
(setq currobj (ssadd (entlast) currobj))
(setq coords (list 
(list 319.4375 -200.58) 
(list 245.415 -212.3664) 
(list 245.415 -212.5434) 
(list 319.4375 -200.657)))
(apply 'command (append '("pline") coords '("c")))
(setq currobj (ssadd (entlast) currobj))
(command "_layer" "set" "nitride" "")
(command "_layer" "set" "text" "")
(command "_circle" "318.985,-211.8" "0.075")
(command "_circle" "318.985,-211.5" "0.075")
(command "_circle" "318.985,-211.2" "0.075")
(command "_circle" "318.985,-210.9" "0.075")
(command "_circle" "318.985,-210.6" "0.075")
(command "_circle" "318.685,-211.8" "0.075")
(command "_circle" "318.685,-211.5" "0.075")
(command "_circle" "318.685,-211.2" "0.075")
(command "_circle" "318.685,-210.9" "0.075")
(command "_circle" "318.685,-210.6" "0.075")
(command "_circle" "318.385,-211.8" "0.075")
(command "_circle" "318.385,-211.5" "0.075")
(command "_circle" "318.385,-211.2" "0.075")
(command "_circle" "318.385,-210.9" "0.075")
(command "_circle" "318.385,-210.6" "0.075")
(command "_circle" "318.085,-211.8" "0.075")
(command "_circle" "318.085,-211.5" "0.075")
(command "_circle" "318.085,-211.2" "0.075")
(command "_circle" "318.085,-210.9" "0.075")
(command "_circle" "318.085,-210.6" "0.075")
(command "_circle" "317.785,-211.8" "0.075")
(command "_circle" "317.785,-211.5" "0.075")
(command "_circle" "317.785,-211.2" "0.075")
(command "_circle" "317.785,-210.9" "0.075")
(command "_circle" "317.785,-210.6" "0.075")
(command "_layer" "set" "nitride" "")
(setq anglednodearray1 currobj)
(setq currobj nil)
(setq currobj (ssadd))
; DRAWING COOLED SINGLE NANOBEAM
(setq coords (list 
(list 320.2625 -186.357) 
(list 320.2625 -181.357) 
(list 319.7375 -181.357) 
(list 319.7375 -186.357)))
(apply 'command (append '("pline") coords '("c")))
(setq currobj (ssadd (entlast) currobj))
(command "_layer" "set" "prebias" "")
(command "_rectangle" "319.7375,-186.357" "320.2625,-181.357")
(setq currobj (ssadd (entlast) currobj))
(command "_layer" "set" "nitride" "")
(setq coords (list 
(list 320.2625 -181.357) 
(list 320.5625 -171.357) 
(list 320.5625 -171.357) 
(list 320.5625 -170.357) 
(list 394.585 -171.107) 
(list 394.585 -166.164) 
(list 320.5625 -166.914) 
(list 320.5625 -165.914) 
(list 320.5625 -165.914) 
(list 320.2625 -155.914) 
(list 319.7375 -155.914) 
(list 319.4375 -165.914) 
(list 319.4375 -165.914) 
(list 319.4375 -166.914) 
(list 245.415 -166.164) 
(list 245.415 -171.107) 
(list 319.4375 -170.357) 
(list 319.4375 -171.357) 
(list 319.4375 -171.357) 
(list 319.7375 -181.357)))
(apply 'command (append '("pline") coords '("c")))
(setq currobj (ssadd (entlast) currobj))
(command "_layer" "set" "prebias" "")
(setq coords (list 
(list 319.4375 -181.357) 
(list 319.4375 -170.357) 
(list 245.415 -171.107) 
(list 245.415 -166.164) 
(list 319.4375 -166.914) 
(list 319.4375 -155.914) 
(list 320.5625 -155.914) 
(list 320.5625 -166.914) 
(list 394.585 -166.164) 
(list 394.585 -171.107) 
(list 320.5625 -170.357) 
(list 320.5625 -181.357)))
(apply 'command (append '("pline") coords '("c")))
(setq currobj (ssadd (entlast) currobj))
(command "_layer" "set" "nitride" "")
(command "_layer" "set" "fda1" "")
(setq coords (list 
(list 320.5625 -170.214) 
(list 394.585 -170.964) 
(list 394.585 -170.787) 
(list 320.5625 -170.137)))
(apply 'command (append '("pline") coords '("c")))
(setq currobj (ssadd (entlast) currobj))
(setq coords (list 
(list 320.5625 -169.994) 
(list 394.585 -170.644) 
(list 394.585 -170.467) 
(list 320.5625 -169.917)))
(apply 'command (append '("pline") coords '("c")))
(setq currobj (ssadd (entlast) currobj))
(setq coords (list 
(list 320.5625 -169.774) 
(list 394.585 -170.324) 
(list 394.585 -170.147) 
(list 320.5625 -169.697)))
(apply 'command (append '("pline") coords '("c")))
(setq currobj (ssadd (entlast) currobj))
(setq coords (list 
(list 320.5625 -169.554) 
(list 394.585 -170.004) 
(list 394.585 -169.827) 
(list 320.5625 -169.477)))
(apply 'command (append '("pline") coords '("c")))
(setq currobj (ssadd (entlast) currobj))
(setq coords (list 
(list 320.5625 -169.334) 
(list 394.585 -169.684) 
(list 394.585 -169.507) 
(list 320.5625 -169.257)))
(apply 'command (append '("pline") coords '("c")))
(setq currobj (ssadd (entlast) currobj))
(setq coords (list 
(list 320.5625 -169.114) 
(list 394.585 -169.364) 
(list 394.585 -169.187) 
(list 320.5625 -169.037)))
(apply 'command (append '("pline") coords '("c")))
(setq currobj (ssadd (entlast) currobj))
(setq coords (list 
(list 320.5625 -168.894) 
(list 394.585 -169.044) 
(list 394.585 -168.867) 
(list 320.5625 -168.817)))
(apply 'command (append '("pline") coords '("c")))
(setq currobj (ssadd (entlast) currobj))
(setq coords (list 
(list 320.5625 -168.674) 
(list 394.585 -168.724) 
(list 394.585 -168.547) 
(list 320.5625 -168.597)))
(apply 'command (append '("pline") coords '("c")))
(setq currobj (ssadd (entlast) currobj))
(setq coords (list 
(list 320.5625 -168.454) 
(list 394.585 -168.404) 
(list 394.585 -168.227) 
(list 320.5625 -168.377)))
(apply 'command (append '("pline") coords '("c")))
(setq currobj (ssadd (entlast) currobj))
(setq coords (list 
(list 320.5625 -168.234) 
(list 394.585 -168.084) 
(list 394.585 -167.907) 
(list 320.5625 -168.157)))
(apply 'command (append '("pline") coords '("c")))
(setq currobj (ssadd (entlast) currobj))
(setq coords (list 
(list 320.5625 -168.014) 
(list 394.585 -167.764) 
(list 394.585 -167.587) 
(list 320.5625 -167.937)))
(apply 'command (append '("pline") coords '("c")))
(setq currobj (ssadd (entlast) currobj))
(setq coords (list 
(list 320.5625 -167.794) 
(list 394.585 -167.444) 
(list 394.585 -167.267) 
(list 320.5625 -167.717)))
(apply 'command (append '("pline") coords '("c")))
(setq currobj (ssadd (entlast) currobj))
(setq coords (list 
(list 320.5625 -167.574) 
(list 394.585 -167.124) 
(list 394.585 -166.947) 
(list 320.5625 -167.497)))
(apply 'command (append '("pline") coords '("c")))
(setq currobj (ssadd (entlast) currobj))
(setq coords (list 
(list 320.5625 -167.354) 
(list 394.585 -166.804) 
(list 394.585 -166.627) 
(list 320.5625 -167.277)))
(apply 'command (append '("pline") coords '("c")))
(setq currobj (ssadd (entlast) currobj))
(setq coords (list 
(list 320.5625 -167.134) 
(list 394.585 -166.484) 
(list 394.585 -166.307) 
(list 320.5625 -167.057)))
(apply 'command (append '("pline") coords '("c")))
(setq currobj (ssadd (entlast) currobj))
(setq coords (list 
(list 319.4375 -167.057) 
(list 245.415 -166.307) 
(list 245.415 -166.484) 
(list 319.4375 -167.134)))
(apply 'command (append '("pline") coords '("c")))
(setq currobj (ssadd (entlast) currobj))
(setq coords (list 
(list 319.4375 -167.277) 
(list 245.415 -166.627) 
(list 245.415 -166.804) 
(list 319.4375 -167.354)))
(apply 'command (append '("pline") coords '("c")))
(setq currobj (ssadd (entlast) currobj))
(setq coords (list 
(list 319.4375 -167.497) 
(list 245.415 -166.947) 
(list 245.415 -167.124) 
(list 319.4375 -167.574)))
(apply 'command (append '("pline") coords '("c")))
(setq currobj (ssadd (entlast) currobj))
(setq coords (list 
(list 319.4375 -167.717) 
(list 245.415 -167.267) 
(list 245.415 -167.444) 
(list 319.4375 -167.794)))
(apply 'command (append '("pline") coords '("c")))
(setq currobj (ssadd (entlast) currobj))
(setq coords (list 
(list 319.4375 -167.937) 
(list 245.415 -167.587) 
(list 245.415 -167.764) 
(list 319.4375 -168.014)))
(apply 'command (append '("pline") coords '("c")))
(setq currobj (ssadd (entlast) currobj))
(setq coords (list 
(list 319.4375 -168.157) 
(list 245.415 -167.907) 
(list 245.415 -168.084) 
(list 319.4375 -168.234)))
(apply 'command (append '("pline") coords '("c")))
(setq currobj (ssadd (entlast) currobj))
(setq coords (list 
(list 319.4375 -168.377) 
(list 245.415 -168.227) 
(list 245.415 -168.404) 
(list 319.4375 -168.454)))
(apply 'command (append '("pline") coords '("c")))
(setq currobj (ssadd (entlast) currobj))
(setq coords (list 
(list 319.4375 -168.597) 
(list 245.415 -168.547) 
(list 245.415 -168.724) 
(list 319.4375 -168.674)))
(apply 'command (append '("pline") coords '("c")))
(setq currobj (ssadd (entlast) currobj))
(setq coords (list 
(list 319.4375 -168.817) 
(list 245.415 -168.867) 
(list 245.415 -169.044) 
(list 319.4375 -168.894)))
(apply 'command (append '("pline") coords '("c")))
(setq currobj (ssadd (entlast) currobj))
(setq coords (list 
(list 319.4375 -169.037) 
(list 245.415 -169.187) 
(list 245.415 -169.364) 
(list 319.4375 -169.114)))
(apply 'command (append '("pline") coords '("c")))
(setq currobj (ssadd (entlast) currobj))
(setq coords (list 
(list 319.4375 -169.257) 
(list 245.415 -169.507) 
(list 245.415 -169.684) 
(list 319.4375 -169.334)))
(apply 'command (append '("pline") coords '("c")))
(setq currobj (ssadd (entlast) currobj))
(setq coords (list 
(list 319.4375 -169.477) 
(list 245.415 -169.827) 
(list 245.415 -170.004) 
(list 319.4375 -169.554)))
(apply 'command (append '("pline") coords '("c")))
(setq currobj (ssadd (entlast) currobj))
(setq coords (list 
(list 319.4375 -169.697) 
(list 245.415 -170.147) 
(list 245.415 -170.324) 
(list 319.4375 -169.774)))
(apply 'command (append '("pline") coords '("c")))
(setq currobj (ssadd (entlast) currobj))
(setq coords (list 
(list 319.4375 -169.917) 
(list 245.415 -170.467) 
(list 245.415 -170.644) 
(list 319.4375 -169.994)))
(apply 'command (append '("pline") coords '("c")))
(setq currobj (ssadd (entlast) currobj))
(setq coords (list 
(list 319.4375 -170.137) 
(list 245.415 -170.787) 
(list 245.415 -170.964) 
(list 319.4375 -170.214)))
(apply 'command (append '("pline") coords '("c")))
(setq currobj (ssadd (entlast) currobj))
(command "_layer" "set" "nitride" "")
(command "_layer" "set" "text" "")
(command "_circle" "319.0625,-181.357" "0.075")
(command "_circle" "319.0625,-181.057" "0.075")
(command "_circle" "319.0625,-180.757" "0.075")
(command "_circle" "319.0625,-180.457" "0.075")
(command "_circle" "319.0625,-180.157" "0.075")
(command "_circle" "318.7625,-181.357" "0.075")
(command "_circle" "318.7625,-181.057" "0.075")
(command "_circle" "318.7625,-180.757" "0.075")
(command "_circle" "318.7625,-180.457" "0.075")
(command "_circle" "318.7625,-180.157" "0.075")
(command "_circle" "318.4625,-181.357" "0.075")
(command "_circle" "318.4625,-181.057" "0.075")
(command "_circle" "318.4625,-180.757" "0.075")
(command "_circle" "318.4625,-180.457" "0.075")
(command "_circle" "318.4625,-180.157" "0.075")
(command "_circle" "318.1625,-181.357" "0.075")
(command "_circle" "318.1625,-181.057" "0.075")
(command "_circle" "318.1625,-180.757" "0.075")
(command "_circle" "318.1625,-180.457" "0.075")
(command "_circle" "318.1625,-180.157" "0.075")
(command "_circle" "317.8625,-181.357" "0.075")
(command "_circle" "317.8625,-181.057" "0.075")
(command "_circle" "317.8625,-180.757" "0.075")
(command "_circle" "317.8625,-180.457" "0.075")
(command "_circle" "317.8625,-180.157" "0.075")
(command "_layer" "set" "nitride" "")
(setq coords (list 
(list 320.2625 -155.914) 
(list 320.2625 -40.2693) 
(list 319.7375 -40.2693) 
(list 319.7375 -155.914)))
(apply 'command (append '("pline") coords '("c")))
(setq currobj (ssadd (entlast) currobj))
(command "_layer" "set" "prebias" "")
(command "_rectangle" "319.7375,-155.914" "320.2625,-40.2693")
(setq currobj (ssadd (entlast) currobj))
(command "_layer" "set" "nitride" "")
(setq coords (list 
(list 320.2625 -40.2693) 
(list 320.5625 -30.2693) 
(list 320.5625 -30.2693) 
(list 320.5625 -29.2693) 
(list 394.585 -30.0193) 
(list 394.585 -25.0763) 
(list 320.5625 -25.8263) 
(list 320.5625 -24.8263) 
(list 320.5625 -24.8263) 
(list 320.2625 -14.8263) 
(list 319.7375 -14.8263) 
(list 319.4375 -24.8263) 
(list 319.4375 -24.8263) 
(list 319.4375 -25.8263) 
(list 245.415 -25.0763) 
(list 245.415 -30.0193) 
(list 319.4375 -29.2693) 
(list 319.4375 -30.2693) 
(list 319.4375 -30.2693) 
(list 319.7375 -40.2693)))
(apply 'command (append '("pline") coords '("c")))
(setq currobj (ssadd (entlast) currobj))
(command "_layer" "set" "prebias" "")
(setq coords (list 
(list 319.4375 -40.2693) 
(list 319.4375 -29.2693) 
(list 245.415 -30.0193) 
(list 245.415 -25.0763) 
(list 319.4375 -25.8263) 
(list 319.4375 -14.8263) 
(list 320.5625 -14.8263) 
(list 320.5625 -25.8263) 
(list 394.585 -25.0763) 
(list 394.585 -30.0193) 
(list 320.5625 -29.2693) 
(list 320.5625 -40.2693)))
(apply 'command (append '("pline") coords '("c")))
(setq currobj (ssadd (entlast) currobj))
(command "_layer" "set" "nitride" "")
(command "_layer" "set" "fda1" "")
(setq coords (list 
(list 320.5625 -29.1263) 
(list 394.585 -29.8763) 
(list 394.585 -29.6993) 
(list 320.5625 -29.0493)))
(apply 'command (append '("pline") coords '("c")))
(setq currobj (ssadd (entlast) currobj))
(setq coords (list 
(list 320.5625 -28.9063) 
(list 394.585 -29.5563) 
(list 394.585 -29.3793) 
(list 320.5625 -28.8293)))
(apply 'command (append '("pline") coords '("c")))
(setq currobj (ssadd (entlast) currobj))
(setq coords (list 
(list 320.5625 -28.6863) 
(list 394.585 -29.2363) 
(list 394.585 -29.0593) 
(list 320.5625 -28.6093)))
(apply 'command (append '("pline") coords '("c")))
(setq currobj (ssadd (entlast) currobj))
(setq coords (list 
(list 320.5625 -28.4663) 
(list 394.585 -28.9163) 
(list 394.585 -28.7393) 
(list 320.5625 -28.3893)))
(apply 'command (append '("pline") coords '("c")))
(setq currobj (ssadd (entlast) currobj))
(setq coords (list 
(list 320.5625 -28.2463) 
(list 394.585 -28.5963) 
(list 394.585 -28.4193) 
(list 320.5625 -28.1693)))
(apply 'command (append '("pline") coords '("c")))
(setq currobj (ssadd (entlast) currobj))
(setq coords (list 
(list 320.5625 -28.0263) 
(list 394.585 -28.2763) 
(list 394.585 -28.0993) 
(list 320.5625 -27.9493)))
(apply 'command (append '("pline") coords '("c")))
(setq currobj (ssadd (entlast) currobj))
(setq coords (list 
(list 320.5625 -27.8063) 
(list 394.585 -27.9563) 
(list 394.585 -27.7793) 
(list 320.5625 -27.7293)))
(apply 'command (append '("pline") coords '("c")))
(setq currobj (ssadd (entlast) currobj))
(setq coords (list 
(list 320.5625 -27.5863) 
(list 394.585 -27.6363) 
(list 394.585 -27.4593) 
(list 320.5625 -27.5093)))
(apply 'command (append '("pline") coords '("c")))
(setq currobj (ssadd (entlast) currobj))
(setq coords (list 
(list 320.5625 -27.3663) 
(list 394.585 -27.3163) 
(list 394.585 -27.1393) 
(list 320.5625 -27.2893)))
(apply 'command (append '("pline") coords '("c")))
(setq currobj (ssadd (entlast) currobj))
(setq coords (list 
(list 320.5625 -27.1463) 
(list 394.585 -26.9963) 
(list 394.585 -26.8193) 
(list 320.5625 -27.0693)))
(apply 'command (append '("pline") coords '("c")))
(setq currobj (ssadd (entlast) currobj))
(setq coords (list 
(list 320.5625 -26.9263) 
(list 394.585 -26.6763) 
(list 394.585 -26.4993) 
(list 320.5625 -26.8493)))
(apply 'command (append '("pline") coords '("c")))
(setq currobj (ssadd (entlast) currobj))
(setq coords (list 
(list 320.5625 -26.7063) 
(list 394.585 -26.3563) 
(list 394.585 -26.1793) 
(list 320.5625 -26.6293)))
(apply 'command (append '("pline") coords '("c")))
(setq currobj (ssadd (entlast) currobj))
(setq coords (list 
(list 320.5625 -26.4863) 
(list 394.585 -26.0363) 
(list 394.585 -25.8593) 
(list 320.5625 -26.4093)))
(apply 'command (append '("pline") coords '("c")))
(setq currobj (ssadd (entlast) currobj))
(setq coords (list 
(list 320.5625 -26.2663) 
(list 394.585 -25.7163) 
(list 394.585 -25.5393) 
(list 320.5625 -26.1893)))
(apply 'command (append '("pline") coords '("c")))
(setq currobj (ssadd (entlast) currobj))
(setq coords (list 
(list 320.5625 -26.0463) 
(list 394.585 -25.3963) 
(list 394.585 -25.2193) 
(list 320.5625 -25.9693)))
(apply 'command (append '("pline") coords '("c")))
(setq currobj (ssadd (entlast) currobj))
(setq coords (list 
(list 319.4375 -25.9693) 
(list 245.415 -25.2193) 
(list 245.415 -25.3963) 
(list 319.4375 -26.0463)))
(apply 'command (append '("pline") coords '("c")))
(setq currobj (ssadd (entlast) currobj))
(setq coords (list 
(list 319.4375 -26.1893) 
(list 245.415 -25.5393) 
(list 245.415 -25.7163) 
(list 319.4375 -26.2663)))
(apply 'command (append '("pline") coords '("c")))
(setq currobj (ssadd (entlast) currobj))
(setq coords (list 
(list 319.4375 -26.4093) 
(list 245.415 -25.8593) 
(list 245.415 -26.0363) 
(list 319.4375 -26.4863)))
(apply 'command (append '("pline") coords '("c")))
(setq currobj (ssadd (entlast) currobj))
(setq coords (list 
(list 319.4375 -26.6293) 
(list 245.415 -26.1793) 
(list 245.415 -26.3563) 
(list 319.4375 -26.7063)))
(apply 'command (append '("pline") coords '("c")))
(setq currobj (ssadd (entlast) currobj))
(setq coords (list 
(list 319.4375 -26.8493) 
(list 245.415 -26.4993) 
(list 245.415 -26.6763) 
(list 319.4375 -26.9263)))
(apply 'command (append '("pline") coords '("c")))
(setq currobj (ssadd (entlast) currobj))
(setq coords (list 
(list 319.4375 -27.0693) 
(list 245.415 -26.8193) 
(list 245.415 -26.9963) 
(list 319.4375 -27.1463)))
(apply 'command (append '("pline") coords '("c")))
(setq currobj (ssadd (entlast) currobj))
(setq coords (list 
(list 319.4375 -27.2893) 
(list 245.415 -27.1393) 
(list 245.415 -27.3163) 
(list 319.4375 -27.3663)))
(apply 'command (append '("pline") coords '("c")))
(setq currobj (ssadd (entlast) currobj))
(setq coords (list 
(list 319.4375 -27.5093) 
(list 245.415 -27.4593) 
(list 245.415 -27.6363) 
(list 319.4375 -27.5863)))
(apply 'command (append '("pline") coords '("c")))
(setq currobj (ssadd (entlast) currobj))
(setq coords (list 
(list 319.4375 -27.7293) 
(list 245.415 -27.7793) 
(list 245.415 -27.9563) 
(list 319.4375 -27.8063)))
(apply 'command (append '("pline") coords '("c")))
(setq currobj (ssadd (entlast) currobj))
(setq coords (list 
(list 319.4375 -27.9493) 
(list 245.415 -28.0993) 
(list 245.415 -28.2763) 
(list 319.4375 -28.0263)))
(apply 'command (append '("pline") coords '("c")))
(setq currobj (ssadd (entlast) currobj))
(setq coords (list 
(list 319.4375 -28.1693) 
(list 245.415 -28.4193) 
(list 245.415 -28.5963) 
(list 319.4375 -28.2463)))
(apply 'command (append '("pline") coords '("c")))
(setq currobj (ssadd (entlast) currobj))
(setq coords (list 
(list 319.4375 -28.3893) 
(list 245.415 -28.7393) 
(list 245.415 -28.9163) 
(list 319.4375 -28.4663)))
(apply 'command (append '("pline") coords '("c")))
(setq currobj (ssadd (entlast) currobj))
(setq coords (list 
(list 319.4375 -28.6093) 
(list 245.415 -29.0593) 
(list 245.415 -29.2363) 
(list 319.4375 -28.6863)))
(apply 'command (append '("pline") coords '("c")))
(setq currobj (ssadd (entlast) currobj))
(setq coords (list 
(list 319.4375 -28.8293) 
(list 245.415 -29.3793) 
(list 245.415 -29.5563) 
(list 319.4375 -28.9063)))
(apply 'command (append '("pline") coords '("c")))
(setq currobj (ssadd (entlast) currobj))
(setq coords (list 
(list 319.4375 -29.0493) 
(list 245.415 -29.6993) 
(list 245.415 -29.8763) 
(list 319.4375 -29.1263)))
(apply 'command (append '("pline") coords '("c")))
(setq currobj (ssadd (entlast) currobj))
(command "_layer" "set" "nitride" "")
(command "_layer" "set" "text" "")
(command "_circle" "319.0625,-40.2693" "0.075")
(command "_circle" "319.0625,-39.9693" "0.075")
(command "_circle" "319.0625,-39.6693" "0.075")
(command "_circle" "319.0625,-39.3693" "0.075")
(command "_circle" "319.0625,-39.0693" "0.075")
(command "_circle" "318.7625,-40.2693" "0.075")
(command "_circle" "318.7625,-39.9693" "0.075")
(command "_circle" "318.7625,-39.6693" "0.075")
(command "_circle" "318.7625,-39.3693" "0.075")
(command "_circle" "318.7625,-39.0693" "0.075")
(command "_circle" "318.4625,-40.2693" "0.075")
(command "_circle" "318.4625,-39.9693" "0.075")
(command "_circle" "318.4625,-39.6693" "0.075")
(command "_circle" "318.4625,-39.3693" "0.075")
(command "_circle" "318.4625,-39.0693" "0.075")
(command "_circle" "318.1625,-40.2693" "0.075")
(command "_circle" "318.1625,-39.9693" "0.075")
(command "_circle" "318.1625,-39.6693" "0.075")
(command "_circle" "318.1625,-39.3693" "0.075")
(command "_circle" "318.1625,-39.0693" "0.075")
(command "_circle" "317.8625,-40.2693" "0.075")
(command "_circle" "317.8625,-39.9693" "0.075")
(command "_circle" "317.8625,-39.6693" "0.075")
(command "_circle" "317.8625,-39.3693" "0.075")
(command "_circle" "317.8625,-39.0693" "0.075")
(command "_layer" "set" "nitride" "")
(setq coords (list 
(list 320.2625 -14.8263) 
(list 320.2625 100.8184) 
(list 319.7375 100.8184) 
(list 319.7375 -14.8263)))
(apply 'command (append '("pline") coords '("c")))
(setq currobj (ssadd (entlast) currobj))
(command "_layer" "set" "prebias" "")
(command "_rectangle" "319.7375,-14.8263" "320.2625,100.8184")
(setq currobj (ssadd (entlast) currobj))
(command "_layer" "set" "nitride" "")
(setq coords (list 
(list 320.2625 100.8184) 
(list 320.5625 110.8184) 
(list 320.5625 110.8184) 
(list 320.5625 111.8184) 
(list 394.585 111.0684) 
(list 394.585 116.0114) 
(list 320.5625 115.2614) 
(list 320.5625 116.2614) 
(list 320.5625 116.2614) 
(list 320.2625 126.2614) 
(list 319.7375 126.2614) 
(list 319.4375 116.2614) 
(list 319.4375 116.2614) 
(list 319.4375 115.2614) 
(list 245.415 116.0114) 
(list 245.415 111.0684) 
(list 319.4375 111.8184) 
(list 319.4375 110.8184) 
(list 319.4375 110.8184) 
(list 319.7375 100.8184)))
(apply 'command (append '("pline") coords '("c")))
(setq currobj (ssadd (entlast) currobj))
(command "_layer" "set" "prebias" "")
(setq coords (list 
(list 319.4375 100.8184) 
(list 319.4375 111.8184) 
(list 245.415 111.0684) 
(list 245.415 116.0114) 
(list 319.4375 115.2614) 
(list 319.4375 126.2614) 
(list 320.5625 126.2614) 
(list 320.5625 115.2614) 
(list 394.585 116.0114) 
(list 394.585 111.0684) 
(list 320.5625 111.8184) 
(list 320.5625 100.8184)))
(apply 'command (append '("pline") coords '("c")))
(setq currobj (ssadd (entlast) currobj))
(command "_layer" "set" "nitride" "")
(command "_layer" "set" "fda1" "")
(setq coords (list 
(list 320.5625 111.9614) 
(list 394.585 111.2114) 
(list 394.585 111.3884) 
(list 320.5625 112.0384)))
(apply 'command (append '("pline") coords '("c")))
(setq currobj (ssadd (entlast) currobj))
(setq coords (list 
(list 320.5625 112.1814) 
(list 394.585 111.5314) 
(list 394.585 111.7084) 
(list 320.5625 112.2584)))
(apply 'command (append '("pline") coords '("c")))
(setq currobj (ssadd (entlast) currobj))
(setq coords (list 
(list 320.5625 112.4014) 
(list 394.585 111.8514) 
(list 394.585 112.0284) 
(list 320.5625 112.4784)))
(apply 'command (append '("pline") coords '("c")))
(setq currobj (ssadd (entlast) currobj))
(setq coords (list 
(list 320.5625 112.6214) 
(list 394.585 112.1714) 
(list 394.585 112.3484) 
(list 320.5625 112.6984)))
(apply 'command (append '("pline") coords '("c")))
(setq currobj (ssadd (entlast) currobj))
(setq coords (list 
(list 320.5625 112.8414) 
(list 394.585 112.4914) 
(list 394.585 112.6684) 
(list 320.5625 112.9184)))
(apply 'command (append '("pline") coords '("c")))
(setq currobj (ssadd (entlast) currobj))
(setq coords (list 
(list 320.5625 113.0614) 
(list 394.585 112.8114) 
(list 394.585 112.9884) 
(list 320.5625 113.1384)))
(apply 'command (append '("pline") coords '("c")))
(setq currobj (ssadd (entlast) currobj))
(setq coords (list 
(list 320.5625 113.2814) 
(list 394.585 113.1314) 
(list 394.585 113.3084) 
(list 320.5625 113.3584)))
(apply 'command (append '("pline") coords '("c")))
(setq currobj (ssadd (entlast) currobj))
(setq coords (list 
(list 320.5625 113.5014) 
(list 394.585 113.4514) 
(list 394.585 113.6284) 
(list 320.5625 113.5784)))
(apply 'command (append '("pline") coords '("c")))
(setq currobj (ssadd (entlast) currobj))
(setq coords (list 
(list 320.5625 113.7214) 
(list 394.585 113.7714) 
(list 394.585 113.9484) 
(list 320.5625 113.7984)))
(apply 'command (append '("pline") coords '("c")))
(setq currobj (ssadd (entlast) currobj))
(setq coords (list 
(list 320.5625 113.9414) 
(list 394.585 114.0914) 
(list 394.585 114.2684) 
(list 320.5625 114.0184)))
(apply 'command (append '("pline") coords '("c")))
(setq currobj (ssadd (entlast) currobj))
(setq coords (list 
(list 320.5625 114.1614) 
(list 394.585 114.4114) 
(list 394.585 114.5884) 
(list 320.5625 114.2384)))
(apply 'command (append '("pline") coords '("c")))
(setq currobj (ssadd (entlast) currobj))
(setq coords (list 
(list 320.5625 114.3814) 
(list 394.585 114.7314) 
(list 394.585 114.9084) 
(list 320.5625 114.4584)))
(apply 'command (append '("pline") coords '("c")))
(setq currobj (ssadd (entlast) currobj))
(setq coords (list 
(list 320.5625 114.6014) 
(list 394.585 115.0514) 
(list 394.585 115.2284) 
(list 320.5625 114.6784)))
(apply 'command (append '("pline") coords '("c")))
(setq currobj (ssadd (entlast) currobj))
(setq coords (list 
(list 320.5625 114.8214) 
(list 394.585 115.3714) 
(list 394.585 115.5484) 
(list 320.5625 114.8984)))
(apply 'command (append '("pline") coords '("c")))
(setq currobj (ssadd (entlast) currobj))
(setq coords (list 
(list 320.5625 115.0414) 
(list 394.585 115.6914) 
(list 394.585 115.8684) 
(list 320.5625 115.1184)))
(apply 'command (append '("pline") coords '("c")))
(setq currobj (ssadd (entlast) currobj))
(setq coords (list 
(list 319.4375 115.1184) 
(list 245.415 115.8684) 
(list 245.415 115.6914) 
(list 319.4375 115.0414)))
(apply 'command (append '("pline") coords '("c")))
(setq currobj (ssadd (entlast) currobj))
(setq coords (list 
(list 319.4375 114.8984) 
(list 245.415 115.5484) 
(list 245.415 115.3714) 
(list 319.4375 114.8214)))
(apply 'command (append '("pline") coords '("c")))
(setq currobj (ssadd (entlast) currobj))
(setq coords (list 
(list 319.4375 114.6784) 
(list 245.415 115.2284) 
(list 245.415 115.0514) 
(list 319.4375 114.6014)))
(apply 'command (append '("pline") coords '("c")))
(setq currobj (ssadd (entlast) currobj))
(setq coords (list 
(list 319.4375 114.4584) 
(list 245.415 114.9084) 
(list 245.415 114.7314) 
(list 319.4375 114.3814)))
(apply 'command (append '("pline") coords '("c")))
(setq currobj (ssadd (entlast) currobj))
(setq coords (list 
(list 319.4375 114.2384) 
(list 245.415 114.5884) 
(list 245.415 114.4114) 
(list 319.4375 114.1614)))
(apply 'command (append '("pline") coords '("c")))
(setq currobj (ssadd (entlast) currobj))
(setq coords (list 
(list 319.4375 114.0184) 
(list 245.415 114.2684) 
(list 245.415 114.0914) 
(list 319.4375 113.9414)))
(apply 'command (append '("pline") coords '("c")))
(setq currobj (ssadd (entlast) currobj))
(setq coords (list 
(list 319.4375 113.7984) 
(list 245.415 113.9484) 
(list 245.415 113.7714) 
(list 319.4375 113.7214)))
(apply 'command (append '("pline") coords '("c")))
(setq currobj (ssadd (entlast) currobj))
(setq coords (list 
(list 319.4375 113.5784) 
(list 245.415 113.6284) 
(list 245.415 113.4514) 
(list 319.4375 113.5014)))
(apply 'command (append '("pline") coords '("c")))
(setq currobj (ssadd (entlast) currobj))
(setq coords (list 
(list 319.4375 113.3584) 
(list 245.415 113.3084) 
(list 245.415 113.1314) 
(list 319.4375 113.2814)))
(apply 'command (append '("pline") coords '("c")))
(setq currobj (ssadd (entlast) currobj))
(setq coords (list 
(list 319.4375 113.1384) 
(list 245.415 112.9884) 
(list 245.415 112.8114) 
(list 319.4375 113.0614)))
(apply 'command (append '("pline") coords '("c")))
(setq currobj (ssadd (entlast) currobj))
(setq coords (list 
(list 319.4375 112.9184) 
(list 245.415 112.6684) 
(list 245.415 112.4914) 
(list 319.4375 112.8414)))
(apply 'command (append '("pline") coords '("c")))
(setq currobj (ssadd (entlast) currobj))
(setq coords (list 
(list 319.4375 112.6984) 
(list 245.415 112.3484) 
(list 245.415 112.1714) 
(list 319.4375 112.6214)))
(apply 'command (append '("pline") coords '("c")))
(setq currobj (ssadd (entlast) currobj))
(setq coords (list 
(list 319.4375 112.4784) 
(list 245.415 112.0284) 
(list 245.415 111.8514) 
(list 319.4375 112.4014)))
(apply 'command (append '("pline") coords '("c")))
(setq currobj (ssadd (entlast) currobj))
(setq coords (list 
(list 319.4375 112.2584) 
(list 245.415 111.7084) 
(list 245.415 111.5314) 
(list 319.4375 112.1814)))
(apply 'command (append '("pline") coords '("c")))
(setq currobj (ssadd (entlast) currobj))
(setq coords (list 
(list 319.4375 112.0384) 
(list 245.415 111.3884) 
(list 245.415 111.2114) 
(list 319.4375 111.9614)))
(apply 'command (append '("pline") coords '("c")))
(setq currobj (ssadd (entlast) currobj))
(command "_layer" "set" "nitride" "")
(command "_layer" "set" "text" "")
(command "_circle" "319.0625,100.8184" "0.075")
(command "_circle" "319.0625,101.1184" "0.075")
(command "_circle" "319.0625,101.4184" "0.075")
(command "_circle" "319.0625,101.7184" "0.075")
(command "_circle" "319.0625,102.0184" "0.075")
(command "_circle" "318.7625,100.8184" "0.075")
(command "_circle" "318.7625,101.1184" "0.075")
(command "_circle" "318.7625,101.4184" "0.075")
(command "_circle" "318.7625,101.7184" "0.075")
(command "_circle" "318.7625,102.0184" "0.075")
(command "_circle" "318.4625,100.8184" "0.075")
(command "_circle" "318.4625,101.1184" "0.075")
(command "_circle" "318.4625,101.4184" "0.075")
(command "_circle" "318.4625,101.7184" "0.075")
(command "_circle" "318.4625,102.0184" "0.075")
(command "_circle" "318.1625,100.8184" "0.075")
(command "_circle" "318.1625,101.1184" "0.075")
(command "_circle" "318.1625,101.4184" "0.075")
(command "_circle" "318.1625,101.7184" "0.075")
(command "_circle" "318.1625,102.0184" "0.075")
(command "_circle" "317.8625,100.8184" "0.075")
(command "_circle" "317.8625,101.1184" "0.075")
(command "_circle" "317.8625,101.4184" "0.075")
(command "_circle" "317.8625,101.7184" "0.075")
(command "_circle" "317.8625,102.0184" "0.075")
(command "_layer" "set" "nitride" "")
(setq coords (list 
(list 320.2625 126.2614) 
(list 320.2625 241.9061) 
(list 319.7375 241.9061) 
(list 319.7375 126.2614)))
(apply 'command (append '("pline") coords '("c")))
(setq currobj (ssadd (entlast) currobj))
(command "_layer" "set" "prebias" "")
(command "_rectangle" "319.7375,126.2614" "320.2625,241.9061")
(setq currobj (ssadd (entlast) currobj))
(command "_layer" "set" "nitride" "")
(setq coords (list 
(list 320.2625 241.9061) 
(list 320.5625 251.9061) 
(list 320.5625 251.9061) 
(list 320.5625 252.9061) 
(list 394.585 252.1561) 
(list 394.585 257.0991) 
(list 320.5625 256.3491) 
(list 320.5625 257.3491) 
(list 320.5625 257.3491) 
(list 320.2625 267.3491) 
(list 319.7375 267.3491) 
(list 319.4375 257.3491) 
(list 319.4375 257.3491) 
(list 319.4375 256.3491) 
(list 245.415 257.0991) 
(list 245.415 252.1561) 
(list 319.4375 252.9061) 
(list 319.4375 251.9061) 
(list 319.4375 251.9061) 
(list 319.7375 241.9061)))
(apply 'command (append '("pline") coords '("c")))
(setq currobj (ssadd (entlast) currobj))
(command "_layer" "set" "prebias" "")
(setq coords (list 
(list 319.4375 241.9061) 
(list 319.4375 252.9061) 
(list 245.415 252.1561) 
(list 245.415 257.0991) 
(list 319.4375 256.3491) 
(list 319.4375 267.3491) 
(list 320.5625 267.3491) 
(list 320.5625 256.3491) 
(list 394.585 257.0991) 
(list 394.585 252.1561) 
(list 320.5625 252.9061) 
(list 320.5625 241.9061)))
(apply 'command (append '("pline") coords '("c")))
(setq currobj (ssadd (entlast) currobj))
(command "_layer" "set" "nitride" "")
(command "_layer" "set" "fda1" "")
(setq coords (list 
(list 320.5625 253.0491) 
(list 394.585 252.2991) 
(list 394.585 252.4761) 
(list 320.5625 253.1261)))
(apply 'command (append '("pline") coords '("c")))
(setq currobj (ssadd (entlast) currobj))
(setq coords (list 
(list 320.5625 253.2691) 
(list 394.585 252.6191) 
(list 394.585 252.7961) 
(list 320.5625 253.3461)))
(apply 'command (append '("pline") coords '("c")))
(setq currobj (ssadd (entlast) currobj))
(setq coords (list 
(list 320.5625 253.4891) 
(list 394.585 252.9391) 
(list 394.585 253.1161) 
(list 320.5625 253.5661)))
(apply 'command (append '("pline") coords '("c")))
(setq currobj (ssadd (entlast) currobj))
(setq coords (list 
(list 320.5625 253.7091) 
(list 394.585 253.2591) 
(list 394.585 253.4361) 
(list 320.5625 253.7861)))
(apply 'command (append '("pline") coords '("c")))
(setq currobj (ssadd (entlast) currobj))
(setq coords (list 
(list 320.5625 253.9291) 
(list 394.585 253.5791) 
(list 394.585 253.7561) 
(list 320.5625 254.0061)))
(apply 'command (append '("pline") coords '("c")))
(setq currobj (ssadd (entlast) currobj))
(setq coords (list 
(list 320.5625 254.1491) 
(list 394.585 253.8991) 
(list 394.585 254.0761) 
(list 320.5625 254.2261)))
(apply 'command (append '("pline") coords '("c")))
(setq currobj (ssadd (entlast) currobj))
(setq coords (list 
(list 320.5625 254.3691) 
(list 394.585 254.2191) 
(list 394.585 254.3961) 
(list 320.5625 254.4461)))
(apply 'command (append '("pline") coords '("c")))
(setq currobj (ssadd (entlast) currobj))
(setq coords (list 
(list 320.5625 254.5891) 
(list 394.585 254.5391) 
(list 394.585 254.7161) 
(list 320.5625 254.6661)))
(apply 'command (append '("pline") coords '("c")))
(setq currobj (ssadd (entlast) currobj))
(setq coords (list 
(list 320.5625 254.8091) 
(list 394.585 254.8591) 
(list 394.585 255.0361) 
(list 320.5625 254.8861)))
(apply 'command (append '("pline") coords '("c")))
(setq currobj (ssadd (entlast) currobj))
(setq coords (list 
(list 320.5625 255.0291) 
(list 394.585 255.1791) 
(list 394.585 255.3561) 
(list 320.5625 255.1061)))
(apply 'command (append '("pline") coords '("c")))
(setq currobj (ssadd (entlast) currobj))
(setq coords (list 
(list 320.5625 255.2491) 
(list 394.585 255.4991) 
(list 394.585 255.6761) 
(list 320.5625 255.3261)))
(apply 'command (append '("pline") coords '("c")))
(setq currobj (ssadd (entlast) currobj))
(setq coords (list 
(list 320.5625 255.4691) 
(list 394.585 255.8191) 
(list 394.585 255.9961) 
(list 320.5625 255.5461)))
(apply 'command (append '("pline") coords '("c")))
(setq currobj (ssadd (entlast) currobj))
(setq coords (list 
(list 320.5625 255.6891) 
(list 394.585 256.1391) 
(list 394.585 256.3161) 
(list 320.5625 255.7661)))
(apply 'command (append '("pline") coords '("c")))
(setq currobj (ssadd (entlast) currobj))
(setq coords (list 
(list 320.5625 255.9091) 
(list 394.585 256.4591) 
(list 394.585 256.6361) 
(list 320.5625 255.9861)))
(apply 'command (append '("pline") coords '("c")))
(setq currobj (ssadd (entlast) currobj))
(setq coords (list 
(list 320.5625 256.1291) 
(list 394.585 256.7791) 
(list 394.585 256.9561) 
(list 320.5625 256.2061)))
(apply 'command (append '("pline") coords '("c")))
(setq currobj (ssadd (entlast) currobj))
(setq coords (list 
(list 319.4375 256.2061) 
(list 245.415 256.9561) 
(list 245.415 256.7791) 
(list 319.4375 256.1291)))
(apply 'command (append '("pline") coords '("c")))
(setq currobj (ssadd (entlast) currobj))
(setq coords (list 
(list 319.4375 255.9861) 
(list 245.415 256.6361) 
(list 245.415 256.4591) 
(list 319.4375 255.9091)))
(apply 'command (append '("pline") coords '("c")))
(setq currobj (ssadd (entlast) currobj))
(setq coords (list 
(list 319.4375 255.7661) 
(list 245.415 256.3161) 
(list 245.415 256.1391) 
(list 319.4375 255.6891)))
(apply 'command (append '("pline") coords '("c")))
(setq currobj (ssadd (entlast) currobj))
(setq coords (list 
(list 319.4375 255.5461) 
(list 245.415 255.9961) 
(list 245.415 255.8191) 
(list 319.4375 255.4691)))
(apply 'command (append '("pline") coords '("c")))
(setq currobj (ssadd (entlast) currobj))
(setq coords (list 
(list 319.4375 255.3261) 
(list 245.415 255.6761) 
(list 245.415 255.4991) 
(list 319.4375 255.2491)))
(apply 'command (append '("pline") coords '("c")))
(setq currobj (ssadd (entlast) currobj))
(setq coords (list 
(list 319.4375 255.1061) 
(list 245.415 255.3561) 
(list 245.415 255.1791) 
(list 319.4375 255.0291)))
(apply 'command (append '("pline") coords '("c")))
(setq currobj (ssadd (entlast) currobj))
(setq coords (list 
(list 319.4375 254.8861) 
(list 245.415 255.0361) 
(list 245.415 254.8591) 
(list 319.4375 254.8091)))
(apply 'command (append '("pline") coords '("c")))
(setq currobj (ssadd (entlast) currobj))
(setq coords (list 
(list 319.4375 254.6661) 
(list 245.415 254.7161) 
(list 245.415 254.5391) 
(list 319.4375 254.5891)))
(apply 'command (append '("pline") coords '("c")))
(setq currobj (ssadd (entlast) currobj))
(setq coords (list 
(list 319.4375 254.4461) 
(list 245.415 254.3961) 
(list 245.415 254.2191) 
(list 319.4375 254.3691)))
(apply 'command (append '("pline") coords '("c")))
(setq currobj (ssadd (entlast) currobj))
(setq coords (list 
(list 319.4375 254.2261) 
(list 245.415 254.0761) 
(list 245.415 253.8991) 
(list 319.4375 254.1491)))
(apply 'command (append '("pline") coords '("c")))
(setq currobj (ssadd (entlast) currobj))
(setq coords (list 
(list 319.4375 254.0061) 
(list 245.415 253.7561) 
(list 245.415 253.5791) 
(list 319.4375 253.9291)))
(apply 'command (append '("pline") coords '("c")))
(setq currobj (ssadd (entlast) currobj))
(setq coords (list 
(list 319.4375 253.7861) 
(list 245.415 253.4361) 
(list 245.415 253.2591) 
(list 319.4375 253.7091)))
(apply 'command (append '("pline") coords '("c")))
(setq currobj (ssadd (entlast) currobj))
(setq coords (list 
(list 319.4375 253.5661) 
(list 245.415 253.1161) 
(list 245.415 252.9391) 
(list 319.4375 253.4891)))
(apply 'command (append '("pline") coords '("c")))
(setq currobj (ssadd (entlast) currobj))
(setq coords (list 
(list 319.4375 253.3461) 
(list 245.415 252.7961) 
(list 245.415 252.6191) 
(list 319.4375 253.2691)))
(apply 'command (append '("pline") coords '("c")))
(setq currobj (ssadd (entlast) currobj))
(setq coords (list 
(list 319.4375 253.1261) 
(list 245.415 252.4761) 
(list 245.415 252.2991) 
(list 319.4375 253.0491)))
(apply 'command (append '("pline") coords '("c")))
(setq currobj (ssadd (entlast) currobj))
(command "_layer" "set" "nitride" "")
(command "_layer" "set" "text" "")
(command "_circle" "319.0625,241.9061" "0.075")
(command "_circle" "319.0625,242.2061" "0.075")
(command "_circle" "319.0625,242.5061" "0.075")
(command "_circle" "319.0625,242.8061" "0.075")
(command "_circle" "319.0625,243.1061" "0.075")
(command "_circle" "318.7625,241.9061" "0.075")
(command "_circle" "318.7625,242.2061" "0.075")
(command "_circle" "318.7625,242.5061" "0.075")
(command "_circle" "318.7625,242.8061" "0.075")
(command "_circle" "318.7625,243.1061" "0.075")
(command "_circle" "318.4625,241.9061" "0.075")
(command "_circle" "318.4625,242.2061" "0.075")
(command "_circle" "318.4625,242.5061" "0.075")
(command "_circle" "318.4625,242.8061" "0.075")
(command "_circle" "318.4625,243.1061" "0.075")
(command "_circle" "318.1625,241.9061" "0.075")
(command "_circle" "318.1625,242.2061" "0.075")
(command "_circle" "318.1625,242.5061" "0.075")
(command "_circle" "318.1625,242.8061" "0.075")
(command "_circle" "318.1625,243.1061" "0.075")
(command "_circle" "317.8625,241.9061" "0.075")
(command "_circle" "317.8625,242.2061" "0.075")
(command "_circle" "317.8625,242.5061" "0.075")
(command "_circle" "317.8625,242.8061" "0.075")
(command "_circle" "317.8625,243.1061" "0.075")
(command "_layer" "set" "nitride" "")
(setq coords (list 
(list 320.2625 267.3491) 
(list 320.2625 382.9939) 
(list 319.7375 382.9939) 
(list 319.7375 267.3491)))
(apply 'command (append '("pline") coords '("c")))
(setq currobj (ssadd (entlast) currobj))
(command "_layer" "set" "prebias" "")
(command "_rectangle" "319.7375,267.3491" "320.2625,382.9939")
(setq currobj (ssadd (entlast) currobj))
(command "_layer" "set" "nitride" "")
(setq coords (list 
(list 320.2625 382.9939) 
(list 320.5625 392.9939) 
(list 320.5625 392.9939) 
(list 320.5625 393.9939) 
(list 394.585 393.2439) 
(list 394.585 398.1869) 
(list 320.5625 397.4369) 
(list 320.5625 398.4369) 
(list 320.5625 398.4369) 
(list 320.2625 408.4369) 
(list 319.7375 408.4369) 
(list 319.4375 398.4369) 
(list 319.4375 398.4369) 
(list 319.4375 397.4369) 
(list 245.415 398.1869) 
(list 245.415 393.2439) 
(list 319.4375 393.9939) 
(list 319.4375 392.9939) 
(list 319.4375 392.9939) 
(list 319.7375 382.9939)))
(apply 'command (append '("pline") coords '("c")))
(setq currobj (ssadd (entlast) currobj))
(command "_layer" "set" "prebias" "")
(setq coords (list 
(list 319.4375 382.9939) 
(list 319.4375 393.9939) 
(list 245.415 393.2439) 
(list 245.415 398.1869) 
(list 319.4375 397.4369) 
(list 319.4375 408.4369) 
(list 320.5625 408.4369) 
(list 320.5625 397.4369) 
(list 394.585 398.1869) 
(list 394.585 393.2439) 
(list 320.5625 393.9939) 
(list 320.5625 382.9939)))
(apply 'command (append '("pline") coords '("c")))
(setq currobj (ssadd (entlast) currobj))
(command "_layer" "set" "nitride" "")
(command "_layer" "set" "fda1" "")
(setq coords (list 
(list 320.5625 394.1369) 
(list 394.585 393.3869) 
(list 394.585 393.5639) 
(list 320.5625 394.2139)))
(apply 'command (append '("pline") coords '("c")))
(setq currobj (ssadd (entlast) currobj))
(setq coords (list 
(list 320.5625 394.3569) 
(list 394.585 393.7069) 
(list 394.585 393.8839) 
(list 320.5625 394.4339)))
(apply 'command (append '("pline") coords '("c")))
(setq currobj (ssadd (entlast) currobj))
(setq coords (list 
(list 320.5625 394.5769) 
(list 394.585 394.0269) 
(list 394.585 394.2039) 
(list 320.5625 394.6539)))
(apply 'command (append '("pline") coords '("c")))
(setq currobj (ssadd (entlast) currobj))
(setq coords (list 
(list 320.5625 394.7969) 
(list 394.585 394.3469) 
(list 394.585 394.5239) 
(list 320.5625 394.8739)))
(apply 'command (append '("pline") coords '("c")))
(setq currobj (ssadd (entlast) currobj))
(setq coords (list 
(list 320.5625 395.0169) 
(list 394.585 394.6669) 
(list 394.585 394.8439) 
(list 320.5625 395.0939)))
(apply 'command (append '("pline") coords '("c")))
(setq currobj (ssadd (entlast) currobj))
(setq coords (list 
(list 320.5625 395.2369) 
(list 394.585 394.9869) 
(list 394.585 395.1639) 
(list 320.5625 395.3139)))
(apply 'command (append '("pline") coords '("c")))
(setq currobj (ssadd (entlast) currobj))
(setq coords (list 
(list 320.5625 395.4569) 
(list 394.585 395.3069) 
(list 394.585 395.4839) 
(list 320.5625 395.5339)))
(apply 'command (append '("pline") coords '("c")))
(setq currobj (ssadd (entlast) currobj))
(setq coords (list 
(list 320.5625 395.6769) 
(list 394.585 395.6269) 
(list 394.585 395.8039) 
(list 320.5625 395.7539)))
(apply 'command (append '("pline") coords '("c")))
(setq currobj (ssadd (entlast) currobj))
(setq coords (list 
(list 320.5625 395.8969) 
(list 394.585 395.9469) 
(list 394.585 396.1239) 
(list 320.5625 395.9739)))
(apply 'command (append '("pline") coords '("c")))
(setq currobj (ssadd (entlast) currobj))
(setq coords (list 
(list 320.5625 396.1169) 
(list 394.585 396.2669) 
(list 394.585 396.4439) 
(list 320.5625 396.1939)))
(apply 'command (append '("pline") coords '("c")))
(setq currobj (ssadd (entlast) currobj))
(setq coords (list 
(list 320.5625 396.3369) 
(list 394.585 396.5869) 
(list 394.585 396.7639) 
(list 320.5625 396.4139)))
(apply 'command (append '("pline") coords '("c")))
(setq currobj (ssadd (entlast) currobj))
(setq coords (list 
(list 320.5625 396.5569) 
(list 394.585 396.9069) 
(list 394.585 397.0839) 
(list 320.5625 396.6339)))
(apply 'command (append '("pline") coords '("c")))
(setq currobj (ssadd (entlast) currobj))
(setq coords (list 
(list 320.5625 396.7769) 
(list 394.585 397.2269) 
(list 394.585 397.4039) 
(list 320.5625 396.8539)))
(apply 'command (append '("pline") coords '("c")))
(setq currobj (ssadd (entlast) currobj))
(setq coords (list 
(list 320.5625 396.9969) 
(list 394.585 397.5469) 
(list 394.585 397.7239) 
(list 320.5625 397.0739)))
(apply 'command (append '("pline") coords '("c")))
(setq currobj (ssadd (entlast) currobj))
(setq coords (list 
(list 320.5625 397.2169) 
(list 394.585 397.8669) 
(list 394.585 398.0439) 
(list 320.5625 397.2939)))
(apply 'command (append '("pline") coords '("c")))
(setq currobj (ssadd (entlast) currobj))
(setq coords (list 
(list 319.4375 397.2939) 
(list 245.415 398.0439) 
(list 245.415 397.8669) 
(list 319.4375 397.2169)))
(apply 'command (append '("pline") coords '("c")))
(setq currobj (ssadd (entlast) currobj))
(setq coords (list 
(list 319.4375 397.0739) 
(list 245.415 397.7239) 
(list 245.415 397.5469) 
(list 319.4375 396.9969)))
(apply 'command (append '("pline") coords '("c")))
(setq currobj (ssadd (entlast) currobj))
(setq coords (list 
(list 319.4375 396.8539) 
(list 245.415 397.4039) 
(list 245.415 397.2269) 
(list 319.4375 396.7769)))
(apply 'command (append '("pline") coords '("c")))
(setq currobj (ssadd (entlast) currobj))
(setq coords (list 
(list 319.4375 396.6339) 
(list 245.415 397.0839) 
(list 245.415 396.9069) 
(list 319.4375 396.5569)))
(apply 'command (append '("pline") coords '("c")))
(setq currobj (ssadd (entlast) currobj))
(setq coords (list 
(list 319.4375 396.4139) 
(list 245.415 396.7639) 
(list 245.415 396.5869) 
(list 319.4375 396.3369)))
(apply 'command (append '("pline") coords '("c")))
(setq currobj (ssadd (entlast) currobj))
(setq coords (list 
(list 319.4375 396.1939) 
(list 245.415 396.4439) 
(list 245.415 396.2669) 
(list 319.4375 396.1169)))
(apply 'command (append '("pline") coords '("c")))
(setq currobj (ssadd (entlast) currobj))
(setq coords (list 
(list 319.4375 395.9739) 
(list 245.415 396.1239) 
(list 245.415 395.9469) 
(list 319.4375 395.8969)))
(apply 'command (append '("pline") coords '("c")))
(setq currobj (ssadd (entlast) currobj))
(setq coords (list 
(list 319.4375 395.7539) 
(list 245.415 395.8039) 
(list 245.415 395.6269) 
(list 319.4375 395.6769)))
(apply 'command (append '("pline") coords '("c")))
(setq currobj (ssadd (entlast) currobj))
(setq coords (list 
(list 319.4375 395.5339) 
(list 245.415 395.4839) 
(list 245.415 395.3069) 
(list 319.4375 395.4569)))
(apply 'command (append '("pline") coords '("c")))
(setq currobj (ssadd (entlast) currobj))
(setq coords (list 
(list 319.4375 395.3139) 
(list 245.415 395.1639) 
(list 245.415 394.9869) 
(list 319.4375 395.2369)))
(apply 'command (append '("pline") coords '("c")))
(setq currobj (ssadd (entlast) currobj))
(setq coords (list 
(list 319.4375 395.0939) 
(list 245.415 394.8439) 
(list 245.415 394.6669) 
(list 319.4375 395.0169)))
(apply 'command (append '("pline") coords '("c")))
(setq currobj (ssadd (entlast) currobj))
(setq coords (list 
(list 319.4375 394.8739) 
(list 245.415 394.5239) 
(list 245.415 394.3469) 
(list 319.4375 394.7969)))
(apply 'command (append '("pline") coords '("c")))
(setq currobj (ssadd (entlast) currobj))
(setq coords (list 
(list 319.4375 394.6539) 
(list 245.415 394.2039) 
(list 245.415 394.0269) 
(list 319.4375 394.5769)))
(apply 'command (append '("pline") coords '("c")))
(setq currobj (ssadd (entlast) currobj))
(setq coords (list 
(list 319.4375 394.4339) 
(list 245.415 393.8839) 
(list 245.415 393.7069) 
(list 319.4375 394.3569)))
(apply 'command (append '("pline") coords '("c")))
(setq currobj (ssadd (entlast) currobj))
(setq coords (list 
(list 319.4375 394.2139) 
(list 245.415 393.5639) 
(list 245.415 393.3869) 
(list 319.4375 394.1369)))
(apply 'command (append '("pline") coords '("c")))
(setq currobj (ssadd (entlast) currobj))
(command "_layer" "set" "nitride" "")
(command "_layer" "set" "text" "")
(command "_circle" "319.0625,382.9939" "0.075")
(command "_circle" "319.0625,383.2939" "0.075")
(command "_circle" "319.0625,383.5939" "0.075")
(command "_circle" "319.0625,383.8939" "0.075")
(command "_circle" "319.0625,384.1939" "0.075")
(command "_circle" "318.7625,382.9939" "0.075")
(command "_circle" "318.7625,383.2939" "0.075")
(command "_circle" "318.7625,383.5939" "0.075")
(command "_circle" "318.7625,383.8939" "0.075")
(command "_circle" "318.7625,384.1939" "0.075")
(command "_circle" "318.4625,382.9939" "0.075")
(command "_circle" "318.4625,383.2939" "0.075")
(command "_circle" "318.4625,383.5939" "0.075")
(command "_circle" "318.4625,383.8939" "0.075")
(command "_circle" "318.4625,384.1939" "0.075")
(command "_circle" "318.1625,382.9939" "0.075")
(command "_circle" "318.1625,383.2939" "0.075")
(command "_circle" "318.1625,383.5939" "0.075")
(command "_circle" "318.1625,383.8939" "0.075")
(command "_circle" "318.1625,384.1939" "0.075")
(command "_circle" "317.8625,382.9939" "0.075")
(command "_circle" "317.8625,383.2939" "0.075")
(command "_circle" "317.8625,383.5939" "0.075")
(command "_circle" "317.8625,383.8939" "0.075")
(command "_circle" "317.8625,384.1939" "0.075")
(command "_layer" "set" "nitride" "")
(setq coords (list 
(list 320.2625 408.4369) 
(list 320.2625 524.0816) 
(list 319.7375 524.0816) 
(list 319.7375 408.4369)))
(apply 'command (append '("pline") coords '("c")))
(setq currobj (ssadd (entlast) currobj))
(command "_layer" "set" "prebias" "")
(command "_rectangle" "319.7375,408.4369" "320.2625,524.0816")
(setq currobj (ssadd (entlast) currobj))
(command "_layer" "set" "nitride" "")
(setq coords (list 
(list 320.2625 524.0816) 
(list 320.5625 534.0816) 
(list 320.5625 534.0816) 
(list 320.5625 535.0816) 
(list 394.585 534.3316) 
(list 394.585 539.2746) 
(list 320.5625 538.5246) 
(list 320.5625 539.5246) 
(list 320.5625 539.5246) 
(list 320.2625 549.5246) 
(list 319.7375 549.5246) 
(list 319.4375 539.5246) 
(list 319.4375 539.5246) 
(list 319.4375 538.5246) 
(list 245.415 539.2746) 
(list 245.415 534.3316) 
(list 319.4375 535.0816) 
(list 319.4375 534.0816) 
(list 319.4375 534.0816) 
(list 319.7375 524.0816)))
(apply 'command (append '("pline") coords '("c")))
(setq currobj (ssadd (entlast) currobj))
(command "_layer" "set" "prebias" "")
(setq coords (list 
(list 319.4375 524.0816) 
(list 319.4375 535.0816) 
(list 245.415 534.3316) 
(list 245.415 539.2746) 
(list 319.4375 538.5246) 
(list 319.4375 549.5246) 
(list 320.5625 549.5246) 
(list 320.5625 538.5246) 
(list 394.585 539.2746) 
(list 394.585 534.3316) 
(list 320.5625 535.0816) 
(list 320.5625 524.0816)))
(apply 'command (append '("pline") coords '("c")))
(setq currobj (ssadd (entlast) currobj))
(command "_layer" "set" "nitride" "")
(command "_layer" "set" "fda1" "")
(setq coords (list 
(list 320.5625 535.2246) 
(list 394.585 534.4746) 
(list 394.585 534.6516) 
(list 320.5625 535.3016)))
(apply 'command (append '("pline") coords '("c")))
(setq currobj (ssadd (entlast) currobj))
(setq coords (list 
(list 320.5625 535.4446) 
(list 394.585 534.7946) 
(list 394.585 534.9716) 
(list 320.5625 535.5216)))
(apply 'command (append '("pline") coords '("c")))
(setq currobj (ssadd (entlast) currobj))
(setq coords (list 
(list 320.5625 535.6646) 
(list 394.585 535.1146) 
(list 394.585 535.2916) 
(list 320.5625 535.7416)))
(apply 'command (append '("pline") coords '("c")))
(setq currobj (ssadd (entlast) currobj))
(setq coords (list 
(list 320.5625 535.8846) 
(list 394.585 535.4346) 
(list 394.585 535.6116) 
(list 320.5625 535.9616)))
(apply 'command (append '("pline") coords '("c")))
(setq currobj (ssadd (entlast) currobj))
(setq coords (list 
(list 320.5625 536.1046) 
(list 394.585 535.7546) 
(list 394.585 535.9316) 
(list 320.5625 536.1816)))
(apply 'command (append '("pline") coords '("c")))
(setq currobj (ssadd (entlast) currobj))
(setq coords (list 
(list 320.5625 536.3246) 
(list 394.585 536.0746) 
(list 394.585 536.2516) 
(list 320.5625 536.4016)))
(apply 'command (append '("pline") coords '("c")))
(setq currobj (ssadd (entlast) currobj))
(setq coords (list 
(list 320.5625 536.5446) 
(list 394.585 536.3946) 
(list 394.585 536.5716) 
(list 320.5625 536.6216)))
(apply 'command (append '("pline") coords '("c")))
(setq currobj (ssadd (entlast) currobj))
(setq coords (list 
(list 320.5625 536.7646) 
(list 394.585 536.7146) 
(list 394.585 536.8916) 
(list 320.5625 536.8416)))
(apply 'command (append '("pline") coords '("c")))
(setq currobj (ssadd (entlast) currobj))
(setq coords (list 
(list 320.5625 536.9846) 
(list 394.585 537.0346) 
(list 394.585 537.2116) 
(list 320.5625 537.0616)))
(apply 'command (append '("pline") coords '("c")))
(setq currobj (ssadd (entlast) currobj))
(setq coords (list 
(list 320.5625 537.2046) 
(list 394.585 537.3546) 
(list 394.585 537.5316) 
(list 320.5625 537.2816)))
(apply 'command (append '("pline") coords '("c")))
(setq currobj (ssadd (entlast) currobj))
(setq coords (list 
(list 320.5625 537.4246) 
(list 394.585 537.6746) 
(list 394.585 537.8516) 
(list 320.5625 537.5016)))
(apply 'command (append '("pline") coords '("c")))
(setq currobj (ssadd (entlast) currobj))
(setq coords (list 
(list 320.5625 537.6446) 
(list 394.585 537.9946) 
(list 394.585 538.1716) 
(list 320.5625 537.7216)))
(apply 'command (append '("pline") coords '("c")))
(setq currobj (ssadd (entlast) currobj))
(setq coords (list 
(list 320.5625 537.8646) 
(list 394.585 538.3146) 
(list 394.585 538.4916) 
(list 320.5625 537.9416)))
(apply 'command (append '("pline") coords '("c")))
(setq currobj (ssadd (entlast) currobj))
(setq coords (list 
(list 320.5625 538.0846) 
(list 394.585 538.6346) 
(list 394.585 538.8116) 
(list 320.5625 538.1616)))
(apply 'command (append '("pline") coords '("c")))
(setq currobj (ssadd (entlast) currobj))
(setq coords (list 
(list 320.5625 538.3046) 
(list 394.585 538.9546) 
(list 394.585 539.1316) 
(list 320.5625 538.3816)))
(apply 'command (append '("pline") coords '("c")))
(setq currobj (ssadd (entlast) currobj))
(setq coords (list 
(list 319.4375 538.3816) 
(list 245.415 539.1316) 
(list 245.415 538.9546) 
(list 319.4375 538.3046)))
(apply 'command (append '("pline") coords '("c")))
(setq currobj (ssadd (entlast) currobj))
(setq coords (list 
(list 319.4375 538.1616) 
(list 245.415 538.8116) 
(list 245.415 538.6346) 
(list 319.4375 538.0846)))
(apply 'command (append '("pline") coords '("c")))
(setq currobj (ssadd (entlast) currobj))
(setq coords (list 
(list 319.4375 537.9416) 
(list 245.415 538.4916) 
(list 245.415 538.3146) 
(list 319.4375 537.8646)))
(apply 'command (append '("pline") coords '("c")))
(setq currobj (ssadd (entlast) currobj))
(setq coords (list 
(list 319.4375 537.7216) 
(list 245.415 538.1716) 
(list 245.415 537.9946) 
(list 319.4375 537.6446)))
(apply 'command (append '("pline") coords '("c")))
(setq currobj (ssadd (entlast) currobj))
(setq coords (list 
(list 319.4375 537.5016) 
(list 245.415 537.8516) 
(list 245.415 537.6746) 
(list 319.4375 537.4246)))
(apply 'command (append '("pline") coords '("c")))
(setq currobj (ssadd (entlast) currobj))
(setq coords (list 
(list 319.4375 537.2816) 
(list 245.415 537.5316) 
(list 245.415 537.3546) 
(list 319.4375 537.2046)))
(apply 'command (append '("pline") coords '("c")))
(setq currobj (ssadd (entlast) currobj))
(setq coords (list 
(list 319.4375 537.0616) 
(list 245.415 537.2116) 
(list 245.415 537.0346) 
(list 319.4375 536.9846)))
(apply 'command (append '("pline") coords '("c")))
(setq currobj (ssadd (entlast) currobj))
(setq coords (list 
(list 319.4375 536.8416) 
(list 245.415 536.8916) 
(list 245.415 536.7146) 
(list 319.4375 536.7646)))
(apply 'command (append '("pline") coords '("c")))
(setq currobj (ssadd (entlast) currobj))
(setq coords (list 
(list 319.4375 536.6216) 
(list 245.415 536.5716) 
(list 245.415 536.3946) 
(list 319.4375 536.5446)))
(apply 'command (append '("pline") coords '("c")))
(setq currobj (ssadd (entlast) currobj))
(setq coords (list 
(list 319.4375 536.4016) 
(list 245.415 536.2516) 
(list 245.415 536.0746) 
(list 319.4375 536.3246)))
(apply 'command (append '("pline") coords '("c")))
(setq currobj (ssadd (entlast) currobj))
(setq coords (list 
(list 319.4375 536.1816) 
(list 245.415 535.9316) 
(list 245.415 535.7546) 
(list 319.4375 536.1046)))
(apply 'command (append '("pline") coords '("c")))
(setq currobj (ssadd (entlast) currobj))
(setq coords (list 
(list 319.4375 535.9616) 
(list 245.415 535.6116) 
(list 245.415 535.4346) 
(list 319.4375 535.8846)))
(apply 'command (append '("pline") coords '("c")))
(setq currobj (ssadd (entlast) currobj))
(setq coords (list 
(list 319.4375 535.7416) 
(list 245.415 535.2916) 
(list 245.415 535.1146) 
(list 319.4375 535.6646)))
(apply 'command (append '("pline") coords '("c")))
(setq currobj (ssadd (entlast) currobj))
(setq coords (list 
(list 319.4375 535.5216) 
(list 245.415 534.9716) 
(list 245.415 534.7946) 
(list 319.4375 535.4446)))
(apply 'command (append '("pline") coords '("c")))
(setq currobj (ssadd (entlast) currobj))
(setq coords (list 
(list 319.4375 535.3016) 
(list 245.415 534.6516) 
(list 245.415 534.4746) 
(list 319.4375 535.2246)))
(apply 'command (append '("pline") coords '("c")))
(setq currobj (ssadd (entlast) currobj))
(command "_layer" "set" "nitride" "")
(command "_layer" "set" "text" "")
(command "_circle" "319.0625,524.0816" "0.075")
(command "_circle" "319.0625,524.3816" "0.075")
(command "_circle" "319.0625,524.6816" "0.075")
(command "_circle" "319.0625,524.9816" "0.075")
(command "_circle" "319.0625,525.2816" "0.075")
(command "_circle" "318.7625,524.0816" "0.075")
(command "_circle" "318.7625,524.3816" "0.075")
(command "_circle" "318.7625,524.6816" "0.075")
(command "_circle" "318.7625,524.9816" "0.075")
(command "_circle" "318.7625,525.2816" "0.075")
(command "_circle" "318.4625,524.0816" "0.075")
(command "_circle" "318.4625,524.3816" "0.075")
(command "_circle" "318.4625,524.6816" "0.075")
(command "_circle" "318.4625,524.9816" "0.075")
(command "_circle" "318.4625,525.2816" "0.075")
(command "_circle" "318.1625,524.0816" "0.075")
(command "_circle" "318.1625,524.3816" "0.075")
(command "_circle" "318.1625,524.6816" "0.075")
(command "_circle" "318.1625,524.9816" "0.075")
(command "_circle" "318.1625,525.2816" "0.075")
(command "_circle" "317.8625,524.0816" "0.075")
(command "_circle" "317.8625,524.3816" "0.075")
(command "_circle" "317.8625,524.6816" "0.075")
(command "_circle" "317.8625,524.9816" "0.075")
(command "_circle" "317.8625,525.2816" "0.075")
(command "_layer" "set" "nitride" "")
(setq coords (list 
(list 320.2625 549.5246) 
(list 320.2625 665.1693) 
(list 319.7375 665.1693) 
(list 319.7375 549.5246)))
(apply 'command (append '("pline") coords '("c")))
(setq currobj (ssadd (entlast) currobj))
(command "_layer" "set" "prebias" "")
(command "_rectangle" "319.7375,549.5246" "320.2625,665.1693")
(setq currobj (ssadd (entlast) currobj))
(command "_layer" "set" "nitride" "")
(setq coords (list 
(list 320.2625 665.1693) 
(list 320.5625 675.1693) 
(list 320.5625 675.1693) 
(list 320.5625 676.1693) 
(list 394.585 675.4193) 
(list 394.585 680.3623) 
(list 320.5625 679.6123) 
(list 320.5625 680.6123) 
(list 320.5625 680.6123) 
(list 320.2625 690.6123) 
(list 319.7375 690.6123) 
(list 319.4375 680.6123) 
(list 319.4375 680.6123) 
(list 319.4375 679.6123) 
(list 245.415 680.3623) 
(list 245.415 675.4193) 
(list 319.4375 676.1693) 
(list 319.4375 675.1693) 
(list 319.4375 675.1693) 
(list 319.7375 665.1693)))
(apply 'command (append '("pline") coords '("c")))
(setq currobj (ssadd (entlast) currobj))
(command "_layer" "set" "prebias" "")
(setq coords (list 
(list 319.4375 665.1693) 
(list 319.4375 676.1693) 
(list 245.415 675.4193) 
(list 245.415 680.3623) 
(list 319.4375 679.6123) 
(list 319.4375 690.6123) 
(list 320.5625 690.6123) 
(list 320.5625 679.6123) 
(list 394.585 680.3623) 
(list 394.585 675.4193) 
(list 320.5625 676.1693) 
(list 320.5625 665.1693)))
(apply 'command (append '("pline") coords '("c")))
(setq currobj (ssadd (entlast) currobj))
(command "_layer" "set" "nitride" "")
(command "_layer" "set" "fda1" "")
(setq coords (list 
(list 320.5625 676.3123) 
(list 394.585 675.5623) 
(list 394.585 675.7393) 
(list 320.5625 676.3893)))
(apply 'command (append '("pline") coords '("c")))
(setq currobj (ssadd (entlast) currobj))
(setq coords (list 
(list 320.5625 676.5323) 
(list 394.585 675.8823) 
(list 394.585 676.0593) 
(list 320.5625 676.6093)))
(apply 'command (append '("pline") coords '("c")))
(setq currobj (ssadd (entlast) currobj))
(setq coords (list 
(list 320.5625 676.7523) 
(list 394.585 676.2023) 
(list 394.585 676.3793) 
(list 320.5625 676.8293)))
(apply 'command (append '("pline") coords '("c")))
(setq currobj (ssadd (entlast) currobj))
(setq coords (list 
(list 320.5625 676.9723) 
(list 394.585 676.5223) 
(list 394.585 676.6993) 
(list 320.5625 677.0493)))
(apply 'command (append '("pline") coords '("c")))
(setq currobj (ssadd (entlast) currobj))
(setq coords (list 
(list 320.5625 677.1923) 
(list 394.585 676.8423) 
(list 394.585 677.0193) 
(list 320.5625 677.2693)))
(apply 'command (append '("pline") coords '("c")))
(setq currobj (ssadd (entlast) currobj))
(setq coords (list 
(list 320.5625 677.4123) 
(list 394.585 677.1623) 
(list 394.585 677.3393) 
(list 320.5625 677.4893)))
(apply 'command (append '("pline") coords '("c")))
(setq currobj (ssadd (entlast) currobj))
(setq coords (list 
(list 320.5625 677.6323) 
(list 394.585 677.4823) 
(list 394.585 677.6593) 
(list 320.5625 677.7093)))
(apply 'command (append '("pline") coords '("c")))
(setq currobj (ssadd (entlast) currobj))
(setq coords (list 
(list 320.5625 677.8523) 
(list 394.585 677.8023) 
(list 394.585 677.9793) 
(list 320.5625 677.9293)))
(apply 'command (append '("pline") coords '("c")))
(setq currobj (ssadd (entlast) currobj))
(setq coords (list 
(list 320.5625 678.0723) 
(list 394.585 678.1223) 
(list 394.585 678.2993) 
(list 320.5625 678.1493)))
(apply 'command (append '("pline") coords '("c")))
(setq currobj (ssadd (entlast) currobj))
(setq coords (list 
(list 320.5625 678.2923) 
(list 394.585 678.4423) 
(list 394.585 678.6193) 
(list 320.5625 678.3693)))
(apply 'command (append '("pline") coords '("c")))
(setq currobj (ssadd (entlast) currobj))
(setq coords (list 
(list 320.5625 678.5123) 
(list 394.585 678.7623) 
(list 394.585 678.9393) 
(list 320.5625 678.5893)))
(apply 'command (append '("pline") coords '("c")))
(setq currobj (ssadd (entlast) currobj))
(setq coords (list 
(list 320.5625 678.7323) 
(list 394.585 679.0823) 
(list 394.585 679.2593) 
(list 320.5625 678.8093)))
(apply 'command (append '("pline") coords '("c")))
(setq currobj (ssadd (entlast) currobj))
(setq coords (list 
(list 320.5625 678.9523) 
(list 394.585 679.4023) 
(list 394.585 679.5793) 
(list 320.5625 679.0293)))
(apply 'command (append '("pline") coords '("c")))
(setq currobj (ssadd (entlast) currobj))
(setq coords (list 
(list 320.5625 679.1723) 
(list 394.585 679.7223) 
(list 394.585 679.8993) 
(list 320.5625 679.2493)))
(apply 'command (append '("pline") coords '("c")))
(setq currobj (ssadd (entlast) currobj))
(setq coords (list 
(list 320.5625 679.3923) 
(list 394.585 680.0423) 
(list 394.585 680.2193) 
(list 320.5625 679.4693)))
(apply 'command (append '("pline") coords '("c")))
(setq currobj (ssadd (entlast) currobj))
(setq coords (list 
(list 319.4375 679.4693) 
(list 245.415 680.2193) 
(list 245.415 680.0423) 
(list 319.4375 679.3923)))
(apply 'command (append '("pline") coords '("c")))
(setq currobj (ssadd (entlast) currobj))
(setq coords (list 
(list 319.4375 679.2493) 
(list 245.415 679.8993) 
(list 245.415 679.7223) 
(list 319.4375 679.1723)))
(apply 'command (append '("pline") coords '("c")))
(setq currobj (ssadd (entlast) currobj))
(setq coords (list 
(list 319.4375 679.0293) 
(list 245.415 679.5793) 
(list 245.415 679.4023) 
(list 319.4375 678.9523)))
(apply 'command (append '("pline") coords '("c")))
(setq currobj (ssadd (entlast) currobj))
(setq coords (list 
(list 319.4375 678.8093) 
(list 245.415 679.2593) 
(list 245.415 679.0823) 
(list 319.4375 678.7323)))
(apply 'command (append '("pline") coords '("c")))
(setq currobj (ssadd (entlast) currobj))
(setq coords (list 
(list 319.4375 678.5893) 
(list 245.415 678.9393) 
(list 245.415 678.7623) 
(list 319.4375 678.5123)))
(apply 'command (append '("pline") coords '("c")))
(setq currobj (ssadd (entlast) currobj))
(setq coords (list 
(list 319.4375 678.3693) 
(list 245.415 678.6193) 
(list 245.415 678.4423) 
(list 319.4375 678.2923)))
(apply 'command (append '("pline") coords '("c")))
(setq currobj (ssadd (entlast) currobj))
(setq coords (list 
(list 319.4375 678.1493) 
(list 245.415 678.2993) 
(list 245.415 678.1223) 
(list 319.4375 678.0723)))
(apply 'command (append '("pline") coords '("c")))
(setq currobj (ssadd (entlast) currobj))
(setq coords (list 
(list 319.4375 677.9293) 
(list 245.415 677.9793) 
(list 245.415 677.8023) 
(list 319.4375 677.8523)))
(apply 'command (append '("pline") coords '("c")))
(setq currobj (ssadd (entlast) currobj))
(setq coords (list 
(list 319.4375 677.7093) 
(list 245.415 677.6593) 
(list 245.415 677.4823) 
(list 319.4375 677.6323)))
(apply 'command (append '("pline") coords '("c")))
(setq currobj (ssadd (entlast) currobj))
(setq coords (list 
(list 319.4375 677.4893) 
(list 245.415 677.3393) 
(list 245.415 677.1623) 
(list 319.4375 677.4123)))
(apply 'command (append '("pline") coords '("c")))
(setq currobj (ssadd (entlast) currobj))
(setq coords (list 
(list 319.4375 677.2693) 
(list 245.415 677.0193) 
(list 245.415 676.8423) 
(list 319.4375 677.1923)))
(apply 'command (append '("pline") coords '("c")))
(setq currobj (ssadd (entlast) currobj))
(setq coords (list 
(list 319.4375 677.0493) 
(list 245.415 676.6993) 
(list 245.415 676.5223) 
(list 319.4375 676.9723)))
(apply 'command (append '("pline") coords '("c")))
(setq currobj (ssadd (entlast) currobj))
(setq coords (list 
(list 319.4375 676.8293) 
(list 245.415 676.3793) 
(list 245.415 676.2023) 
(list 319.4375 676.7523)))
(apply 'command (append '("pline") coords '("c")))
(setq currobj (ssadd (entlast) currobj))
(setq coords (list 
(list 319.4375 676.6093) 
(list 245.415 676.0593) 
(list 245.415 675.8823) 
(list 319.4375 676.5323)))
(apply 'command (append '("pline") coords '("c")))
(setq currobj (ssadd (entlast) currobj))
(setq coords (list 
(list 319.4375 676.3893) 
(list 245.415 675.7393) 
(list 245.415 675.5623) 
(list 319.4375 676.3123)))
(apply 'command (append '("pline") coords '("c")))
(setq currobj (ssadd (entlast) currobj))
(command "_layer" "set" "nitride" "")
(command "_layer" "set" "text" "")
(command "_circle" "319.0625,665.1693" "0.075")
(command "_circle" "319.0625,665.4693" "0.075")
(command "_circle" "319.0625,665.7693" "0.075")
(command "_circle" "319.0625,666.0693" "0.075")
(command "_circle" "319.0625,666.3693" "0.075")
(command "_circle" "318.7625,665.1693" "0.075")
(command "_circle" "318.7625,665.4693" "0.075")
(command "_circle" "318.7625,665.7693" "0.075")
(command "_circle" "318.7625,666.0693" "0.075")
(command "_circle" "318.7625,666.3693" "0.075")
(command "_circle" "318.4625,665.1693" "0.075")
(command "_circle" "318.4625,665.4693" "0.075")
(command "_circle" "318.4625,665.7693" "0.075")
(command "_circle" "318.4625,666.0693" "0.075")
(command "_circle" "318.4625,666.3693" "0.075")
(command "_circle" "318.1625,665.1693" "0.075")
(command "_circle" "318.1625,665.4693" "0.075")
(command "_circle" "318.1625,665.7693" "0.075")
(command "_circle" "318.1625,666.0693" "0.075")
(command "_circle" "318.1625,666.3693" "0.075")
(command "_circle" "317.8625,665.1693" "0.075")
(command "_circle" "317.8625,665.4693" "0.075")
(command "_circle" "317.8625,665.7693" "0.075")
(command "_circle" "317.8625,666.0693" "0.075")
(command "_circle" "317.8625,666.3693" "0.075")
(command "_layer" "set" "nitride" "")
(setq coords (list 
(list 320.2625 690.6123) 
(list 320.2625 806.257) 
(list 319.7375 806.257) 
(list 319.7375 690.6123)))
(apply 'command (append '("pline") coords '("c")))
(setq currobj (ssadd (entlast) currobj))
(command "_layer" "set" "prebias" "")
(command "_rectangle" "319.7375,690.6123" "320.2625,806.257")
(setq currobj (ssadd (entlast) currobj))
(command "_layer" "set" "nitride" "")
(setq coords (list 
(list 320.2625 806.257) 
(list 320.5625 816.257) 
(list 320.5625 816.257) 
(list 320.5625 817.257) 
(list 394.585 816.507) 
(list 394.585 821.45) 
(list 320.5625 820.7) 
(list 320.5625 821.7) 
(list 320.5625 821.7) 
(list 320.2625 831.7) 
(list 319.7375 831.7) 
(list 319.4375 821.7) 
(list 319.4375 821.7) 
(list 319.4375 820.7) 
(list 245.415 821.45) 
(list 245.415 816.507) 
(list 319.4375 817.257) 
(list 319.4375 816.257) 
(list 319.4375 816.257) 
(list 319.7375 806.257)))
(apply 'command (append '("pline") coords '("c")))
(setq currobj (ssadd (entlast) currobj))
(command "_layer" "set" "prebias" "")
(setq coords (list 
(list 319.4375 806.257) 
(list 319.4375 817.257) 
(list 245.415 816.507) 
(list 245.415 821.45) 
(list 319.4375 820.7) 
(list 319.4375 831.7) 
(list 320.5625 831.7) 
(list 320.5625 820.7) 
(list 394.585 821.45) 
(list 394.585 816.507) 
(list 320.5625 817.257) 
(list 320.5625 806.257)))
(apply 'command (append '("pline") coords '("c")))
(setq currobj (ssadd (entlast) currobj))
(command "_layer" "set" "nitride" "")
(command "_layer" "set" "fda1" "")
(setq coords (list 
(list 320.5625 817.4) 
(list 394.585 816.65) 
(list 394.585 816.827) 
(list 320.5625 817.477)))
(apply 'command (append '("pline") coords '("c")))
(setq currobj (ssadd (entlast) currobj))
(setq coords (list 
(list 320.5625 817.62) 
(list 394.585 816.97) 
(list 394.585 817.147) 
(list 320.5625 817.697)))
(apply 'command (append '("pline") coords '("c")))
(setq currobj (ssadd (entlast) currobj))
(setq coords (list 
(list 320.5625 817.84) 
(list 394.585 817.29) 
(list 394.585 817.467) 
(list 320.5625 817.917)))
(apply 'command (append '("pline") coords '("c")))
(setq currobj (ssadd (entlast) currobj))
(setq coords (list 
(list 320.5625 818.06) 
(list 394.585 817.61) 
(list 394.585 817.787) 
(list 320.5625 818.137)))
(apply 'command (append '("pline") coords '("c")))
(setq currobj (ssadd (entlast) currobj))
(setq coords (list 
(list 320.5625 818.28) 
(list 394.585 817.93) 
(list 394.585 818.107) 
(list 320.5625 818.357)))
(apply 'command (append '("pline") coords '("c")))
(setq currobj (ssadd (entlast) currobj))
(setq coords (list 
(list 320.5625 818.5) 
(list 394.585 818.25) 
(list 394.585 818.427) 
(list 320.5625 818.577)))
(apply 'command (append '("pline") coords '("c")))
(setq currobj (ssadd (entlast) currobj))
(setq coords (list 
(list 320.5625 818.72) 
(list 394.585 818.57) 
(list 394.585 818.747) 
(list 320.5625 818.797)))
(apply 'command (append '("pline") coords '("c")))
(setq currobj (ssadd (entlast) currobj))
(setq coords (list 
(list 320.5625 818.94) 
(list 394.585 818.89) 
(list 394.585 819.067) 
(list 320.5625 819.017)))
(apply 'command (append '("pline") coords '("c")))
(setq currobj (ssadd (entlast) currobj))
(setq coords (list 
(list 320.5625 819.16) 
(list 394.585 819.21) 
(list 394.585 819.387) 
(list 320.5625 819.237)))
(apply 'command (append '("pline") coords '("c")))
(setq currobj (ssadd (entlast) currobj))
(setq coords (list 
(list 320.5625 819.38) 
(list 394.585 819.53) 
(list 394.585 819.707) 
(list 320.5625 819.457)))
(apply 'command (append '("pline") coords '("c")))
(setq currobj (ssadd (entlast) currobj))
(setq coords (list 
(list 320.5625 819.6) 
(list 394.585 819.85) 
(list 394.585 820.027) 
(list 320.5625 819.677)))
(apply 'command (append '("pline") coords '("c")))
(setq currobj (ssadd (entlast) currobj))
(setq coords (list 
(list 320.5625 819.82) 
(list 394.585 820.17) 
(list 394.585 820.347) 
(list 320.5625 819.897)))
(apply 'command (append '("pline") coords '("c")))
(setq currobj (ssadd (entlast) currobj))
(setq coords (list 
(list 320.5625 820.04) 
(list 394.585 820.49) 
(list 394.585 820.667) 
(list 320.5625 820.117)))
(apply 'command (append '("pline") coords '("c")))
(setq currobj (ssadd (entlast) currobj))
(setq coords (list 
(list 320.5625 820.26) 
(list 394.585 820.81) 
(list 394.585 820.987) 
(list 320.5625 820.337)))
(apply 'command (append '("pline") coords '("c")))
(setq currobj (ssadd (entlast) currobj))
(setq coords (list 
(list 320.5625 820.48) 
(list 394.585 821.13) 
(list 394.585 821.307) 
(list 320.5625 820.557)))
(apply 'command (append '("pline") coords '("c")))
(setq currobj (ssadd (entlast) currobj))
(setq coords (list 
(list 319.4375 820.557) 
(list 245.415 821.307) 
(list 245.415 821.13) 
(list 319.4375 820.48)))
(apply 'command (append '("pline") coords '("c")))
(setq currobj (ssadd (entlast) currobj))
(setq coords (list 
(list 319.4375 820.337) 
(list 245.415 820.987) 
(list 245.415 820.81) 
(list 319.4375 820.26)))
(apply 'command (append '("pline") coords '("c")))
(setq currobj (ssadd (entlast) currobj))
(setq coords (list 
(list 319.4375 820.117) 
(list 245.415 820.667) 
(list 245.415 820.49) 
(list 319.4375 820.04)))
(apply 'command (append '("pline") coords '("c")))
(setq currobj (ssadd (entlast) currobj))
(setq coords (list 
(list 319.4375 819.897) 
(list 245.415 820.347) 
(list 245.415 820.17) 
(list 319.4375 819.82)))
(apply 'command (append '("pline") coords '("c")))
(setq currobj (ssadd (entlast) currobj))
(setq coords (list 
(list 319.4375 819.677) 
(list 245.415 820.027) 
(list 245.415 819.85) 
(list 319.4375 819.6)))
(apply 'command (append '("pline") coords '("c")))
(setq currobj (ssadd (entlast) currobj))
(setq coords (list 
(list 319.4375 819.457) 
(list 245.415 819.707) 
(list 245.415 819.53) 
(list 319.4375 819.38)))
(apply 'command (append '("pline") coords '("c")))
(setq currobj (ssadd (entlast) currobj))
(setq coords (list 
(list 319.4375 819.237) 
(list 245.415 819.387) 
(list 245.415 819.21) 
(list 319.4375 819.16)))
(apply 'command (append '("pline") coords '("c")))
(setq currobj (ssadd (entlast) currobj))
(setq coords (list 
(list 319.4375 819.017) 
(list 245.415 819.067) 
(list 245.415 818.89) 
(list 319.4375 818.94)))
(apply 'command (append '("pline") coords '("c")))
(setq currobj (ssadd (entlast) currobj))
(setq coords (list 
(list 319.4375 818.797) 
(list 245.415 818.747) 
(list 245.415 818.57) 
(list 319.4375 818.72)))
(apply 'command (append '("pline") coords '("c")))
(setq currobj (ssadd (entlast) currobj))
(setq coords (list 
(list 319.4375 818.577) 
(list 245.415 818.427) 
(list 245.415 818.25) 
(list 319.4375 818.5)))
(apply 'command (append '("pline") coords '("c")))
(setq currobj (ssadd (entlast) currobj))
(setq coords (list 
(list 319.4375 818.357) 
(list 245.415 818.107) 
(list 245.415 817.93) 
(list 319.4375 818.28)))
(apply 'command (append '("pline") coords '("c")))
(setq currobj (ssadd (entlast) currobj))
(setq coords (list 
(list 319.4375 818.137) 
(list 245.415 817.787) 
(list 245.415 817.61) 
(list 319.4375 818.06)))
(apply 'command (append '("pline") coords '("c")))
(setq currobj (ssadd (entlast) currobj))
(setq coords (list 
(list 319.4375 817.917) 
(list 245.415 817.467) 
(list 245.415 817.29) 
(list 319.4375 817.84)))
(apply 'command (append '("pline") coords '("c")))
(setq currobj (ssadd (entlast) currobj))
(setq coords (list 
(list 319.4375 817.697) 
(list 245.415 817.147) 
(list 245.415 816.97) 
(list 319.4375 817.62)))
(apply 'command (append '("pline") coords '("c")))
(setq currobj (ssadd (entlast) currobj))
(setq coords (list 
(list 319.4375 817.477) 
(list 245.415 816.827) 
(list 245.415 816.65) 
(list 319.4375 817.4)))
(apply 'command (append '("pline") coords '("c")))
(setq currobj (ssadd (entlast) currobj))
(command "_layer" "set" "nitride" "")
(command "_layer" "set" "text" "")
(command "_circle" "319.0625,806.257" "0.075")
(command "_circle" "319.0625,806.557" "0.075")
(command "_circle" "319.0625,806.857" "0.075")
(command "_circle" "319.0625,807.157" "0.075")
(command "_circle" "319.0625,807.457" "0.075")
(command "_circle" "318.7625,806.257" "0.075")
(command "_circle" "318.7625,806.557" "0.075")
(command "_circle" "318.7625,806.857" "0.075")
(command "_circle" "318.7625,807.157" "0.075")
(command "_circle" "318.7625,807.457" "0.075")
(command "_circle" "318.4625,806.257" "0.075")
(command "_circle" "318.4625,806.557" "0.075")
(command "_circle" "318.4625,806.857" "0.075")
(command "_circle" "318.4625,807.157" "0.075")
(command "_circle" "318.4625,807.457" "0.075")
(command "_circle" "318.1625,806.257" "0.075")
(command "_circle" "318.1625,806.557" "0.075")
(command "_circle" "318.1625,806.857" "0.075")
(command "_circle" "318.1625,807.157" "0.075")
(command "_circle" "318.1625,807.457" "0.075")
(command "_circle" "317.8625,806.257" "0.075")
(command "_circle" "317.8625,806.557" "0.075")
(command "_circle" "317.8625,806.857" "0.075")
(command "_circle" "317.8625,807.157" "0.075")
(command "_circle" "317.8625,807.457" "0.075")
(command "_layer" "set" "nitride" "")
(setq coords (list 
(list 320.2625 831.7) 
(list 320.2625 836.7) 
(list 319.7375 836.7) 
(list 319.7375 831.7)))
(apply 'command (append '("pline") coords '("c")))
(setq currobj (ssadd (entlast) currobj))
(command "_layer" "set" "prebias" "")
(command "_rectangle" "319.7375,831.7" "320.2625,836.7")
(setq currobj (ssadd (entlast) currobj))
(command "_layer" "set" "nitride" "")
(setq cooledsinglenanobeam1 currobj)
(setq currobj nil)
(setq currobj (ssadd))
; DRAWING PHOTONIC CRYSTAL
(command "_layer" "set" "negYjunc" "")
(setq coords (list 
(list 320.135 866.7) 
(list 320 851.7) 
(list 320 866.7)))
(apply 'command (append '("pline") coords '("c")))
(setq currobj (ssadd (entlast) currobj))
(setq coords (list 
(list 320.2625 836.7) 
(list 320.415 866.7) 
(list 321.066 866.7) 
(list 321.066 836.7)))
(apply 'command (append '("pline") coords '("c")))
(setq currobj (ssadd (entlast) currobj))
(setq coords (list 
(list 319.865 866.7) 
(list 320 851.7) 
(list 320 866.7)))
(apply 'command (append '("pline") coords '("c")))
(setq currobj (ssadd (entlast) currobj))
(setq coords (list 
(list 319.7375 836.7) 
(list 319.585 866.7) 
(list 318.934 866.7) 
(list 318.934 836.7)))
(apply 'command (append '("pline") coords '("c")))
(setq currobj (ssadd (entlast) currobj))
(command "_layer" "set" "nitride" "")
(setq yjunction1 currobj)
(setq currobj nil)
(setq currobj (ssadd))
(setq tap1 nil)
(setq tap1 (ssadd))
(command "_layer" "set" "phc" "")
(setq coords (list 
(list 320 866.7) 
(list 320.135 866.7) 
(list 320.135 866.7103) 
(list 320.135 866.7206) 
(list 320.135 866.7308) 
(list 320.135 866.7411) 
(list 320.135 866.7514) 
(list 320.135 866.7617) 
(list 320.135 866.7719) 
(list 320.135 866.7822) 
(list 320.135 866.7925) 
(list 320.135 866.8028) 
(list 320.135 866.8131) 
(list 320.135 866.8233) 
(list 320.135 866.8336) 
(list 320.135 866.8439) 
(list 320.135 866.8542) 
(list 320.135 866.8644) 
(list 320.135 866.8747) 
(list 320.135 866.885) 
(list 320.135 866.8953) 
(list 320.135 866.9056) 
(list 320.135 866.9158) 
(list 320.135 866.9261) 
(list 320.135 866.9364) 
(list 320.135 866.9467) 
(list 320.135 866.9569) 
(list 320.135 866.9672) 
(list 320.135 866.9775) 
(list 320.135 866.9878) 
(list 320.135 866.9981) 
(list 320.135 867.0083) 
(list 320.135 867.0186) 
(list 320.135 867.0289) 
(list 320.135 867.0392) 
(list 320.135 867.0494) 
(list 320.135 867.0597) 
(list 320.135 867.07) 
(list 320 867.07)))
(apply 'command (append '("pline") coords '("c")))
(setq tap1 (ssadd (entlast) tap1))
(command "_mirror" (entlast) "" "320,900" "320,901" "No")
(setq tap1 (ssadd (entlast) tap1))
(setq coords (list 
(list 320.4229 866.7) 
(list 320.415 866.7) 
(list 320.4152 866.7103) 
(list 320.4154 866.7206) 
(list 320.4156 866.7308) 
(list 320.4157 866.7411) 
(list 320.4157 866.7514) 
(list 320.4156 866.7617) 
(list 320.4155 866.7719) 
(list 320.4153 866.7822) 
(list 320.4149 866.7925) 
(list 320.4145 866.8028) 
(list 320.4141 866.8131) 
(list 320.4136 866.8233) 
(list 320.413 866.8336) 
(list 320.4125 866.8439) 
(list 320.412 866.8542) 
(list 320.4115 866.8644) 
(list 320.4111 866.8747) 
(list 320.4108 866.885) 
(list 320.4106 866.8953) 
(list 320.4106 866.9056) 
(list 320.4107 866.9158) 
(list 320.411 866.9261) 
(list 320.4115 866.9364) 
(list 320.4121 866.9467) 
(list 320.4129 866.9569) 
(list 320.4138 866.9672) 
(list 320.4148 866.9775) 
(list 320.4159 866.9878) 
(list 320.417 866.9981) 
(list 320.4182 867.0083) 
(list 320.4193 867.0186) 
(list 320.4203 867.0289) 
(list 320.4212 867.0392) 
(list 320.422 867.0494) 
(list 320.4225 867.0597) 
(list 320.4229 867.07) 
(list 320.4229 867.07)))
(apply 'command (append '("pline") coords '("c")))
(setq tap1 (ssadd (entlast) tap1))
(command "_mirror" (entlast) "" "320,900" "320,901" "No")
(setq tap1 (ssadd (entlast) tap1))
(setq coords (list 
(list 321.066 866.7) 
(list 320.4229 866.7) 
(list 320.4229 866.7103) 
(list 320.4229 866.7206) 
(list 320.4229 866.7308) 
(list 320.4229 866.7411) 
(list 320.4229 866.7514) 
(list 320.4229 866.7617) 
(list 320.4229 866.7719) 
(list 320.4229 866.7822) 
(list 320.4229 866.7925) 
(list 320.4229 866.8028) 
(list 320.4229 866.8131) 
(list 320.4229 866.8233) 
(list 320.4229 866.8336) 
(list 320.4229 866.8439) 
(list 320.4229 866.8542) 
(list 320.4229 866.8644) 
(list 320.4229 866.8747) 
(list 320.4229 866.885) 
(list 320.4229 866.8953) 
(list 320.4229 866.9056) 
(list 320.4229 866.9158) 
(list 320.4229 866.9261) 
(list 320.4229 866.9364) 
(list 320.4229 866.9467) 
(list 320.4229 866.9569) 
(list 320.4229 866.9672) 
(list 320.4229 866.9775) 
(list 320.4229 866.9878) 
(list 320.4229 866.9981) 
(list 320.4229 867.0083) 
(list 320.4229 867.0186) 
(list 320.4229 867.0289) 
(list 320.4229 867.0392) 
(list 320.4229 867.0494) 
(list 320.4229 867.0597) 
(list 320.4229 867.07) 
(list 321.066 867.07)))
(apply 'command (append '("pline") coords '("c")))
(setq tap1 (ssadd (entlast) tap1))
(command "_mirror" (entlast) "" "320,900" "320,901" "No")
(setq tap1 (ssadd (entlast) tap1))
(setq coords (list 
(list 320 867.07) 
(list 320.135 867.07) 
(list 320.135 867.0803) 
(list 320.135 867.0906) 
(list 320.135 867.1008) 
(list 320.135 867.1111) 
(list 320.135 867.1214) 
(list 320.135 867.1317) 
(list 320.135 867.1419) 
(list 320.135 867.1522) 
(list 320.135 867.1625) 
(list 320.135 867.1728) 
(list 320.135 867.1831) 
(list 320.135 867.1933) 
(list 320.135 867.2036) 
(list 320.135 867.2139) 
(list 320.135 867.2242) 
(list 320.135 867.2344) 
(list 320.135 867.2447) 
(list 320.135 867.255) 
(list 320.135 867.2653) 
(list 320.135 867.2756) 
(list 320.135 867.2858) 
(list 320.135 867.2961) 
(list 320.135 867.3064) 
(list 320.135 867.3167) 
(list 320.135 867.3269) 
(list 320.135 867.3372) 
(list 320.135 867.3475) 
(list 320.135 867.3578) 
(list 320.135 867.3681) 
(list 320.135 867.3783) 
(list 320.135 867.3886) 
(list 320.135 867.3989) 
(list 320.135 867.4092) 
(list 320.135 867.4194) 
(list 320.135 867.4297) 
(list 320.135 867.44) 
(list 320 867.44)))
(apply 'command (append '("pline") coords '("c")))
(setq tap1 (ssadd (entlast) tap1))
(command "_mirror" (entlast) "" "320,900" "320,901" "No")
(setq tap1 (ssadd (entlast) tap1))
(setq coords (list 
(list 320.4307 867.07) 
(list 320.4229 867.07) 
(list 320.423 867.0803) 
(list 320.4228 867.0906) 
(list 320.4223 867.1008) 
(list 320.4216 867.1111) 
(list 320.4207 867.1214) 
(list 320.4194 867.1317) 
(list 320.418 867.1419) 
(list 320.4164 867.1522) 
(list 320.4147 867.1625) 
(list 320.4129 867.1728) 
(list 320.411 867.1831) 
(list 320.4092 867.1933) 
(list 320.4075 867.2036) 
(list 320.406 867.2139) 
(list 320.4046 867.2242) 
(list 320.4036 867.2344) 
(list 320.4028 867.2447) 
(list 320.4024 867.255) 
(list 320.4024 867.2653) 
(list 320.4027 867.2756) 
(list 320.4034 867.2858) 
(list 320.4045 867.2961) 
(list 320.406 867.3064) 
(list 320.4078 867.3167) 
(list 320.4098 867.3269) 
(list 320.4121 867.3372) 
(list 320.4145 867.3475) 
(list 320.417 867.3578) 
(list 320.4195 867.3681) 
(list 320.422 867.3783) 
(list 320.4242 867.3886) 
(list 320.4263 867.3989) 
(list 320.428 867.4092) 
(list 320.4293 867.4194) 
(list 320.4303 867.4297) 
(list 320.4307 867.44) 
(list 320.4307 867.44)))
(apply 'command (append '("pline") coords '("c")))
(setq tap1 (ssadd (entlast) tap1))
(command "_mirror" (entlast) "" "320,900" "320,901" "No")
(setq tap1 (ssadd (entlast) tap1))
(setq coords (list 
(list 321.066 867.07) 
(list 320.4307 867.07) 
(list 320.4307 867.0803) 
(list 320.4307 867.0906) 
(list 320.4307 867.1008) 
(list 320.4307 867.1111) 
(list 320.4307 867.1214) 
(list 320.4307 867.1317) 
(list 320.4307 867.1419) 
(list 320.4307 867.1522) 
(list 320.4307 867.1625) 
(list 320.4307 867.1728) 
(list 320.4307 867.1831) 
(list 320.4307 867.1933) 
(list 320.4307 867.2036) 
(list 320.4307 867.2139) 
(list 320.4307 867.2242) 
(list 320.4307 867.2344) 
(list 320.4307 867.2447) 
(list 320.4307 867.255) 
(list 320.4307 867.2653) 
(list 320.4307 867.2756) 
(list 320.4307 867.2858) 
(list 320.4307 867.2961) 
(list 320.4307 867.3064) 
(list 320.4307 867.3167) 
(list 320.4307 867.3269) 
(list 320.4307 867.3372) 
(list 320.4307 867.3475) 
(list 320.4307 867.3578) 
(list 320.4307 867.3681) 
(list 320.4307 867.3783) 
(list 320.4307 867.3886) 
(list 320.4307 867.3989) 
(list 320.4307 867.4092) 
(list 320.4307 867.4194) 
(list 320.4307 867.4297) 
(list 320.4307 867.44) 
(list 321.066 867.44)))
(apply 'command (append '("pline") coords '("c")))
(setq tap1 (ssadd (entlast) tap1))
(command "_mirror" (entlast) "" "320,900" "320,901" "No")
(setq tap1 (ssadd (entlast) tap1))
(setq coords (list 
(list 320 867.44) 
(list 320.135 867.44) 
(list 320.135 867.4503) 
(list 320.135 867.4606) 
(list 320.135 867.4708) 
(list 320.135 867.4811) 
(list 320.135 867.4914) 
(list 320.135 867.5017) 
(list 320.135 867.5119) 
(list 320.135 867.5222) 
(list 320.135 867.5325) 
(list 320.135 867.5428) 
(list 320.135 867.5531) 
(list 320.135 867.5633) 
(list 320.135 867.5736) 
(list 320.135 867.5839) 
(list 320.135 867.5942) 
(list 320.135 867.6044) 
(list 320.135 867.6147) 
(list 320.135 867.625) 
(list 320.135 867.6353) 
(list 320.135 867.6456) 
(list 320.135 867.6558) 
(list 320.135 867.6661) 
(list 320.135 867.6764) 
(list 320.135 867.6867) 
(list 320.135 867.6969) 
(list 320.135 867.7072) 
(list 320.135 867.7175) 
(list 320.135 867.7278) 
(list 320.135 867.7381) 
(list 320.135 867.7483) 
(list 320.135 867.7586) 
(list 320.135 867.7689) 
(list 320.135 867.7792) 
(list 320.135 867.7894) 
(list 320.135 867.7997) 
(list 320.135 867.81) 
(list 320 867.81)))
(apply 'command (append '("pline") coords '("c")))
(setq tap1 (ssadd (entlast) tap1))
(command "_mirror" (entlast) "" "320,900" "320,901" "No")
(setq tap1 (ssadd (entlast) tap1))
(setq coords (list 
(list 320.4386 867.44) 
(list 320.4307 867.44) 
(list 320.4307 867.4503) 
(list 320.4302 867.4606) 
(list 320.4291 867.4708) 
(list 320.4276 867.4811) 
(list 320.4256 867.4914) 
(list 320.4232 867.5017) 
(list 320.4205 867.5119) 
(list 320.4175 867.5222) 
(list 320.4144 867.5325) 
(list 320.4112 867.5428) 
(list 320.408 867.5531) 
(list 320.4049 867.5633) 
(list 320.402 867.5736) 
(list 320.3995 867.5839) 
(list 320.3973 867.5942) 
(list 320.3957 867.6044) 
(list 320.3945 867.6147) 
(list 320.394 867.625) 
(list 320.3941 867.6353) 
(list 320.3948 867.6456) 
(list 320.3961 867.6558) 
(list 320.398 867.6661) 
(list 320.4005 867.6764) 
(list 320.4034 867.6867) 
(list 320.4068 867.6969) 
(list 320.4104 867.7072) 
(list 320.4143 867.7175) 
(list 320.4182 867.7278) 
(list 320.4221 867.7381) 
(list 320.4258 867.7483) 
(list 320.4292 867.7586) 
(list 320.4322 867.7689) 
(list 320.4348 867.7792) 
(list 320.4367 867.7894) 
(list 320.438 867.7997) 
(list 320.4386 867.81) 
(list 320.4386 867.81)))
(apply 'command (append '("pline") coords '("c")))
(setq tap1 (ssadd (entlast) tap1))
(command "_mirror" (entlast) "" "320,900" "320,901" "No")
(setq tap1 (ssadd (entlast) tap1))
(setq coords (list 
(list 321.066 867.44) 
(list 320.4386 867.44) 
(list 320.4386 867.4503) 
(list 320.4386 867.4606) 
(list 320.4386 867.4708) 
(list 320.4386 867.4811) 
(list 320.4386 867.4914) 
(list 320.4386 867.5017) 
(list 320.4386 867.5119) 
(list 320.4386 867.5222) 
(list 320.4386 867.5325) 
(list 320.4386 867.5428) 
(list 320.4386 867.5531) 
(list 320.4386 867.5633) 
(list 320.4386 867.5736) 
(list 320.4386 867.5839) 
(list 320.4386 867.5942) 
(list 320.4386 867.6044) 
(list 320.4386 867.6147) 
(list 320.4386 867.625) 
(list 320.4386 867.6353) 
(list 320.4386 867.6456) 
(list 320.4386 867.6558) 
(list 320.4386 867.6661) 
(list 320.4386 867.6764) 
(list 320.4386 867.6867) 
(list 320.4386 867.6969) 
(list 320.4386 867.7072) 
(list 320.4386 867.7175) 
(list 320.4386 867.7278) 
(list 320.4386 867.7381) 
(list 320.4386 867.7483) 
(list 320.4386 867.7586) 
(list 320.4386 867.7689) 
(list 320.4386 867.7792) 
(list 320.4386 867.7894) 
(list 320.4386 867.7997) 
(list 320.4386 867.81) 
(list 321.066 867.81)))
(apply 'command (append '("pline") coords '("c")))
(setq tap1 (ssadd (entlast) tap1))
(command "_mirror" (entlast) "" "320,900" "320,901" "No")
(setq tap1 (ssadd (entlast) tap1))
(setq coords (list 
(list 320 867.81) 
(list 320.135 867.81) 
(list 320.135 867.8203) 
(list 320.135 867.8306) 
(list 320.135 867.8408) 
(list 320.135 867.8511) 
(list 320.135 867.8614) 
(list 320.135 867.8717) 
(list 320.135 867.8819) 
(list 320.135 867.8922) 
(list 320.135 867.9025) 
(list 320.135 867.9128) 
(list 320.135 867.9231) 
(list 320.135 867.9333) 
(list 320.135 867.9436) 
(list 320.135 867.9539) 
(list 320.135 867.9642) 
(list 320.135 867.9744) 
(list 320.135 867.9847) 
(list 320.135 867.995) 
(list 320.135 868.0053) 
(list 320.135 868.0156) 
(list 320.135 868.0258) 
(list 320.135 868.0361) 
(list 320.135 868.0464) 
(list 320.135 868.0567) 
(list 320.135 868.0669) 
(list 320.135 868.0772) 
(list 320.135 868.0875) 
(list 320.135 868.0978) 
(list 320.135 868.1081) 
(list 320.135 868.1183) 
(list 320.135 868.1286) 
(list 320.135 868.1389) 
(list 320.135 868.1492) 
(list 320.135 868.1594) 
(list 320.135 868.1697) 
(list 320.135 868.18) 
(list 320 868.18)))
(apply 'command (append '("pline") coords '("c")))
(setq tap1 (ssadd (entlast) tap1))
(command "_mirror" (entlast) "" "320,900" "320,901" "No")
(setq tap1 (ssadd (entlast) tap1))
(setq coords (list 
(list 320.4465 867.81) 
(list 320.4386 867.81) 
(list 320.4384 867.8203) 
(list 320.4375 867.8306) 
(list 320.4359 867.8408) 
(list 320.4336 867.8511) 
(list 320.4306 867.8614) 
(list 320.427 867.8717) 
(list 320.423 867.8819) 
(list 320.4187 867.8922) 
(list 320.4141 867.9025) 
(list 320.4095 867.9128) 
(list 320.4049 867.9231) 
(list 320.4006 867.9333) 
(list 320.3965 867.9436) 
(list 320.393 867.9539) 
(list 320.39 867.9642) 
(list 320.3878 867.9744) 
(list 320.3863 867.9847) 
(list 320.3856 867.995) 
(list 320.3858 868.0053) 
(list 320.3869 868.0156) 
(list 320.3888 868.0258) 
(list 320.3915 868.0361) 
(list 320.395 868.0464) 
(list 320.3991 868.0567) 
(list 320.4037 868.0669) 
(list 320.4087 868.0772) 
(list 320.414 868.0875) 
(list 320.4193 868.0978) 
(list 320.4246 868.1081) 
(list 320.4296 868.1183) 
(list 320.4342 868.1286) 
(list 320.4382 868.1389) 
(list 320.4415 868.1492) 
(list 320.4441 868.1594) 
(list 320.4458 868.1697) 
(list 320.4465 868.18) 
(list 320.4465 868.18)))
(apply 'command (append '("pline") coords '("c")))
(setq tap1 (ssadd (entlast) tap1))
(command "_mirror" (entlast) "" "320,900" "320,901" "No")
(setq tap1 (ssadd (entlast) tap1))
(setq coords (list 
(list 321.066 867.81) 
(list 320.4465 867.81) 
(list 320.4465 867.8203) 
(list 320.4465 867.8306) 
(list 320.4465 867.8408) 
(list 320.4465 867.8511) 
(list 320.4465 867.8614) 
(list 320.4465 867.8717) 
(list 320.4465 867.8819) 
(list 320.4465 867.8922) 
(list 320.4465 867.9025) 
(list 320.4465 867.9128) 
(list 320.4465 867.9231) 
(list 320.4465 867.9333) 
(list 320.4465 867.9436) 
(list 320.4465 867.9539) 
(list 320.4465 867.9642) 
(list 320.4465 867.9744) 
(list 320.4465 867.9847) 
(list 320.4465 867.995) 
(list 320.4465 868.0053) 
(list 320.4465 868.0156) 
(list 320.4465 868.0258) 
(list 320.4465 868.0361) 
(list 320.4465 868.0464) 
(list 320.4465 868.0567) 
(list 320.4465 868.0669) 
(list 320.4465 868.0772) 
(list 320.4465 868.0875) 
(list 320.4465 868.0978) 
(list 320.4465 868.1081) 
(list 320.4465 868.1183) 
(list 320.4465 868.1286) 
(list 320.4465 868.1389) 
(list 320.4465 868.1492) 
(list 320.4465 868.1594) 
(list 320.4465 868.1697) 
(list 320.4465 868.18) 
(list 321.066 868.18)))
(apply 'command (append '("pline") coords '("c")))
(setq tap1 (ssadd (entlast) tap1))
(command "_mirror" (entlast) "" "320,900" "320,901" "No")
(setq tap1 (ssadd (entlast) tap1))
(setq coords (list 
(list 320 868.18) 
(list 320.135 868.18) 
(list 320.135 868.1903) 
(list 320.135 868.2006) 
(list 320.135 868.2108) 
(list 320.135 868.2211) 
(list 320.135 868.2314) 
(list 320.135 868.2417) 
(list 320.135 868.2519) 
(list 320.135 868.2622) 
(list 320.135 868.2725) 
(list 320.135 868.2828) 
(list 320.135 868.2931) 
(list 320.135 868.3033) 
(list 320.135 868.3136) 
(list 320.135 868.3239) 
(list 320.135 868.3342) 
(list 320.135 868.3444) 
(list 320.135 868.3547) 
(list 320.135 868.365) 
(list 320.135 868.3753) 
(list 320.135 868.3856) 
(list 320.135 868.3958) 
(list 320.135 868.4061) 
(list 320.135 868.4164) 
(list 320.135 868.4267) 
(list 320.135 868.4369) 
(list 320.135 868.4472) 
(list 320.135 868.4575) 
(list 320.135 868.4678) 
(list 320.135 868.4781) 
(list 320.135 868.4883) 
(list 320.135 868.4986) 
(list 320.135 868.5089) 
(list 320.135 868.5192) 
(list 320.135 868.5294) 
(list 320.135 868.5397) 
(list 320.135 868.55) 
(list 320 868.55)))
(apply 'command (append '("pline") coords '("c")))
(setq tap1 (ssadd (entlast) tap1))
(command "_mirror" (entlast) "" "320,900" "320,901" "No")
(setq tap1 (ssadd (entlast) tap1))
(setq coords (list 
(list 320.4543 868.18) 
(list 320.4465 868.18) 
(list 320.4462 868.1903) 
(list 320.4449 868.2006) 
(list 320.4427 868.2108) 
(list 320.4395 868.2211) 
(list 320.4355 868.2314) 
(list 320.4308 868.2417) 
(list 320.4255 868.2519) 
(list 320.4198 868.2622) 
(list 320.4139 868.2725) 
(list 320.4078 868.2828) 
(list 320.4019 868.2931) 
(list 320.3962 868.3033) 
(list 320.391 868.3136) 
(list 320.3865 868.3239) 
(list 320.3827 868.3342) 
(list 320.3798 868.3444) 
(list 320.378 868.3547) 
(list 320.3772 868.365) 
(list 320.3775 868.3753) 
(list 320.379 868.3856) 
(list 320.3815 868.3958) 
(list 320.385 868.4061) 
(list 320.3895 868.4164) 
(list 320.3948 868.4267) 
(list 320.4007 868.4369) 
(list 320.4071 868.4472) 
(list 320.4137 868.4575) 
(list 320.4205 868.4678) 
(list 320.4271 868.4781) 
(list 320.4334 868.4883) 
(list 320.4391 868.4986) 
(list 320.4442 868.5089) 
(list 320.4483 868.5192) 
(list 320.4515 868.5294) 
(list 320.4535 868.5397) 
(list 320.4543 868.55) 
(list 320.4543 868.55)))
(apply 'command (append '("pline") coords '("c")))
(setq tap1 (ssadd (entlast) tap1))
(command "_mirror" (entlast) "" "320,900" "320,901" "No")
(setq tap1 (ssadd (entlast) tap1))
(setq coords (list 
(list 321.066 868.18) 
(list 320.4543 868.18) 
(list 320.4543 868.1903) 
(list 320.4543 868.2006) 
(list 320.4543 868.2108) 
(list 320.4543 868.2211) 
(list 320.4543 868.2314) 
(list 320.4543 868.2417) 
(list 320.4543 868.2519) 
(list 320.4543 868.2622) 
(list 320.4543 868.2725) 
(list 320.4543 868.2828) 
(list 320.4543 868.2931) 
(list 320.4543 868.3033) 
(list 320.4543 868.3136) 
(list 320.4543 868.3239) 
(list 320.4543 868.3342) 
(list 320.4543 868.3444) 
(list 320.4543 868.3547) 
(list 320.4543 868.365) 
(list 320.4543 868.3753) 
(list 320.4543 868.3856) 
(list 320.4543 868.3958) 
(list 320.4543 868.4061) 
(list 320.4543 868.4164) 
(list 320.4543 868.4267) 
(list 320.4543 868.4369) 
(list 320.4543 868.4472) 
(list 320.4543 868.4575) 
(list 320.4543 868.4678) 
(list 320.4543 868.4781) 
(list 320.4543 868.4883) 
(list 320.4543 868.4986) 
(list 320.4543 868.5089) 
(list 320.4543 868.5192) 
(list 320.4543 868.5294) 
(list 320.4543 868.5397) 
(list 320.4543 868.55) 
(list 321.066 868.55)))
(apply 'command (append '("pline") coords '("c")))
(setq tap1 (ssadd (entlast) tap1))
(command "_mirror" (entlast) "" "320,900" "320,901" "No")
(setq tap1 (ssadd (entlast) tap1))
(setq coords (list 
(list 320 868.55) 
(list 320.135 868.55) 
(list 320.135 868.5603) 
(list 320.135 868.5706) 
(list 320.135 868.5808) 
(list 320.135 868.5911) 
(list 320.135 868.6014) 
(list 320.135 868.6117) 
(list 320.135 868.6219) 
(list 320.135 868.6322) 
(list 320.135 868.6425) 
(list 320.135 868.6528) 
(list 320.135 868.6631) 
(list 320.135 868.6733) 
(list 320.135 868.6836) 
(list 320.135 868.6939) 
(list 320.135 868.7042) 
(list 320.135 868.7144) 
(list 320.135 868.7247) 
(list 320.135 868.735) 
(list 320.135 868.7453) 
(list 320.135 868.7556) 
(list 320.135 868.7658) 
(list 320.135 868.7761) 
(list 320.135 868.7864) 
(list 320.135 868.7967) 
(list 320.135 868.8069) 
(list 320.135 868.8172) 
(list 320.135 868.8275) 
(list 320.135 868.8378) 
(list 320.135 868.8481) 
(list 320.135 868.8583) 
(list 320.135 868.8686) 
(list 320.135 868.8789) 
(list 320.135 868.8892) 
(list 320.135 868.8994) 
(list 320.135 868.9097) 
(list 320.135 868.92) 
(list 320 868.92)))
(apply 'command (append '("pline") coords '("c")))
(setq tap1 (ssadd (entlast) tap1))
(command "_mirror" (entlast) "" "320,900" "320,901" "No")
(setq tap1 (ssadd (entlast) tap1))
(setq coords (list 
(list 320.4622 868.55) 
(list 320.4543 868.55) 
(list 320.4539 868.5603) 
(list 320.4523 868.5706) 
(list 320.4495 868.5808) 
(list 320.4455 868.5911) 
(list 320.4405 868.6014) 
(list 320.4346 868.6117) 
(list 320.4281 868.6219) 
(list 320.421 868.6322) 
(list 320.4136 868.6425) 
(list 320.4061 868.6528) 
(list 320.3988 868.6631) 
(list 320.3919 868.6733) 
(list 320.3855 868.6836) 
(list 320.38 868.6939) 
(list 320.3754 868.7042) 
(list 320.3719 868.7144) 
(list 320.3697 868.7247) 
(list 320.3688 868.735) 
(list 320.3693 868.7453) 
(list 320.3711 868.7556) 
(list 320.3742 868.7658) 
(list 320.3785 868.7761) 
(list 320.384 868.7864) 
(list 320.3904 868.7967) 
(list 320.3976 868.8069) 
(list 320.4054 868.8172) 
(list 320.4135 868.8275) 
(list 320.4216 868.8378) 
(list 320.4296 868.8481) 
(list 320.4372 868.8583) 
(list 320.4441 868.8686) 
(list 320.4501 868.8789) 
(list 320.4551 868.8892) 
(list 320.4588 868.8994) 
(list 320.4612 868.9097) 
(list 320.4622 868.92) 
(list 320.4622 868.92)))
(apply 'command (append '("pline") coords '("c")))
(setq tap1 (ssadd (entlast) tap1))
(command "_mirror" (entlast) "" "320,900" "320,901" "No")
(setq tap1 (ssadd (entlast) tap1))
(setq coords (list 
(list 321.066 868.55) 
(list 320.4622 868.55) 
(list 320.4622 868.5603) 
(list 320.4622 868.5706) 
(list 320.4622 868.5808) 
(list 320.4622 868.5911) 
(list 320.4622 868.6014) 
(list 320.4622 868.6117) 
(list 320.4622 868.6219) 
(list 320.4622 868.6322) 
(list 320.4622 868.6425) 
(list 320.4622 868.6528) 
(list 320.4622 868.6631) 
(list 320.4622 868.6733) 
(list 320.4622 868.6836) 
(list 320.4622 868.6939) 
(list 320.4622 868.7042) 
(list 320.4622 868.7144) 
(list 320.4622 868.7247) 
(list 320.4622 868.735) 
(list 320.4622 868.7453) 
(list 320.4622 868.7556) 
(list 320.4622 868.7658) 
(list 320.4622 868.7761) 
(list 320.4622 868.7864) 
(list 320.4622 868.7967) 
(list 320.4622 868.8069) 
(list 320.4622 868.8172) 
(list 320.4622 868.8275) 
(list 320.4622 868.8378) 
(list 320.4622 868.8481) 
(list 320.4622 868.8583) 
(list 320.4622 868.8686) 
(list 320.4622 868.8789) 
(list 320.4622 868.8892) 
(list 320.4622 868.8994) 
(list 320.4622 868.9097) 
(list 320.4622 868.92) 
(list 321.066 868.92)))
(apply 'command (append '("pline") coords '("c")))
(setq tap1 (ssadd (entlast) tap1))
(command "_mirror" (entlast) "" "320,900" "320,901" "No")
(setq tap1 (ssadd (entlast) tap1))
(setq coords (list 
(list 320 868.92) 
(list 320.135 868.92) 
(list 320.135 868.9303) 
(list 320.135 868.9406) 
(list 320.135 868.9508) 
(list 320.135 868.9611) 
(list 320.135 868.9714) 
(list 320.135 868.9817) 
(list 320.135 868.9919) 
(list 320.135 869.0022) 
(list 320.135 869.0125) 
(list 320.135 869.0228) 
(list 320.135 869.0331) 
(list 320.135 869.0433) 
(list 320.135 869.0536) 
(list 320.135 869.0639) 
(list 320.135 869.0742) 
(list 320.135 869.0844) 
(list 320.135 869.0947) 
(list 320.135 869.105) 
(list 320.135 869.1153) 
(list 320.135 869.1256) 
(list 320.135 869.1358) 
(list 320.135 869.1461) 
(list 320.135 869.1564) 
(list 320.135 869.1667) 
(list 320.135 869.1769) 
(list 320.135 869.1872) 
(list 320.135 869.1975) 
(list 320.135 869.2078) 
(list 320.135 869.2181) 
(list 320.135 869.2283) 
(list 320.135 869.2386) 
(list 320.135 869.2489) 
(list 320.135 869.2592) 
(list 320.135 869.2694) 
(list 320.135 869.2797) 
(list 320.135 869.29) 
(list 320 869.29)))
(apply 'command (append '("pline") coords '("c")))
(setq tap1 (ssadd (entlast) tap1))
(command "_mirror" (entlast) "" "320,900" "320,901" "No")
(setq tap1 (ssadd (entlast) tap1))
(setq coords (list 
(list 320.4701 868.92) 
(list 320.4622 868.92) 
(list 320.4617 868.9303) 
(list 320.4597 868.9406) 
(list 320.4562 868.9508) 
(list 320.4514 868.9611) 
(list 320.4455 868.9714) 
(list 320.4384 868.9817) 
(list 320.4306 868.9919) 
(list 320.4221 869.0022) 
(list 320.4133 869.0125) 
(list 320.4045 869.0228) 
(list 320.3958 869.0331) 
(list 320.3876 869.0433) 
(list 320.38 869.0536) 
(list 320.3735 869.0639) 
(list 320.3681 869.0742) 
(list 320.364 869.0844) 
(list 320.3614 869.0947) 
(list 320.3604 869.105) 
(list 320.361 869.1153) 
(list 320.3631 869.1256) 
(list 320.3669 869.1358) 
(list 320.372 869.1461) 
(list 320.3785 869.1564) 
(list 320.3861 869.1667) 
(list 320.3946 869.1769) 
(list 320.4037 869.1872) 
(list 320.4132 869.1975) 
(list 320.4228 869.2078) 
(list 320.4321 869.2181) 
(list 320.441 869.2283) 
(list 320.449 869.2386) 
(list 320.4561 869.2489) 
(list 320.4619 869.2592) 
(list 320.4662 869.2694) 
(list 320.469 869.2797) 
(list 320.4701 869.29) 
(list 320.4701 869.29)))
(apply 'command (append '("pline") coords '("c")))
(setq tap1 (ssadd (entlast) tap1))
(command "_mirror" (entlast) "" "320,900" "320,901" "No")
(setq tap1 (ssadd (entlast) tap1))
(setq coords (list 
(list 321.066 868.92) 
(list 320.4701 868.92) 
(list 320.4701 868.9303) 
(list 320.4701 868.9406) 
(list 320.4701 868.9508) 
(list 320.4701 868.9611) 
(list 320.4701 868.9714) 
(list 320.4701 868.9817) 
(list 320.4701 868.9919) 
(list 320.4701 869.0022) 
(list 320.4701 869.0125) 
(list 320.4701 869.0228) 
(list 320.4701 869.0331) 
(list 320.4701 869.0433) 
(list 320.4701 869.0536) 
(list 320.4701 869.0639) 
(list 320.4701 869.0742) 
(list 320.4701 869.0844) 
(list 320.4701 869.0947) 
(list 320.4701 869.105) 
(list 320.4701 869.1153) 
(list 320.4701 869.1256) 
(list 320.4701 869.1358) 
(list 320.4701 869.1461) 
(list 320.4701 869.1564) 
(list 320.4701 869.1667) 
(list 320.4701 869.1769) 
(list 320.4701 869.1872) 
(list 320.4701 869.1975) 
(list 320.4701 869.2078) 
(list 320.4701 869.2181) 
(list 320.4701 869.2283) 
(list 320.4701 869.2386) 
(list 320.4701 869.2489) 
(list 320.4701 869.2592) 
(list 320.4701 869.2694) 
(list 320.4701 869.2797) 
(list 320.4701 869.29) 
(list 321.066 869.29)))
(apply 'command (append '("pline") coords '("c")))
(setq tap1 (ssadd (entlast) tap1))
(command "_mirror" (entlast) "" "320,900" "320,901" "No")
(setq tap1 (ssadd (entlast) tap1))
(setq coords (list 
(list 320 869.29) 
(list 320.135 869.29) 
(list 320.135 869.3003) 
(list 320.135 869.3106) 
(list 320.135 869.3208) 
(list 320.135 869.3311) 
(list 320.135 869.3414) 
(list 320.135 869.3517) 
(list 320.135 869.3619) 
(list 320.135 869.3722) 
(list 320.135 869.3825) 
(list 320.135 869.3928) 
(list 320.135 869.4031) 
(list 320.135 869.4133) 
(list 320.135 869.4236) 
(list 320.135 869.4339) 
(list 320.135 869.4442) 
(list 320.135 869.4544) 
(list 320.135 869.4647) 
(list 320.135 869.475) 
(list 320.135 869.4853) 
(list 320.135 869.4956) 
(list 320.135 869.5058) 
(list 320.135 869.5161) 
(list 320.135 869.5264) 
(list 320.135 869.5367) 
(list 320.135 869.5469) 
(list 320.135 869.5572) 
(list 320.135 869.5675) 
(list 320.135 869.5778) 
(list 320.135 869.5881) 
(list 320.135 869.5983) 
(list 320.135 869.6086) 
(list 320.135 869.6189) 
(list 320.135 869.6292) 
(list 320.135 869.6394) 
(list 320.135 869.6497) 
(list 320.135 869.66) 
(list 320 869.66)))
(apply 'command (append '("pline") coords '("c")))
(setq tap1 (ssadd (entlast) tap1))
(command "_mirror" (entlast) "" "320,900" "320,901" "No")
(setq tap1 (ssadd (entlast) tap1))
(setq coords (list 
(list 320.4779 869.29) 
(list 320.4701 869.29) 
(list 320.4694 869.3003) 
(list 320.467 869.3106) 
(list 320.463 869.3208) 
(list 320.4574 869.3311) 
(list 320.4504 869.3414) 
(list 320.4422 869.3517) 
(list 320.4331 869.3619) 
(list 320.4233 869.3722) 
(list 320.4131 869.3825) 
(list 320.4028 869.3928) 
(list 320.3927 869.4031) 
(list 320.3832 869.4133) 
(list 320.3746 869.4236) 
(list 320.367 869.4339) 
(list 320.3608 869.4442) 
(list 320.3561 869.4544) 
(list 320.3532 869.4647) 
(list 320.352 869.475) 
(list 320.3527 869.4853) 
(list 320.3552 869.4956) 
(list 320.3596 869.5058) 
(list 320.3655 869.5161) 
(list 320.373 869.5264) 
(list 320.3818 869.5367) 
(list 320.3915 869.5469) 
(list 320.402 869.5572) 
(list 320.4129 869.5675) 
(list 320.4239 869.5778) 
(list 320.4346 869.5881) 
(list 320.4448 869.5983) 
(list 320.454 869.6086) 
(list 320.462 869.6189) 
(list 320.4687 869.6292) 
(list 320.4736 869.6394) 
(list 320.4767 869.6497) 
(list 320.4779 869.66) 
(list 320.4779 869.66)))
(apply 'command (append '("pline") coords '("c")))
(setq tap1 (ssadd (entlast) tap1))
(command "_mirror" (entlast) "" "320,900" "320,901" "No")
(setq tap1 (ssadd (entlast) tap1))
(setq coords (list 
(list 321.066 869.29) 
(list 320.4779 869.29) 
(list 320.4779 869.3003) 
(list 320.4779 869.3106) 
(list 320.4779 869.3208) 
(list 320.4779 869.3311) 
(list 320.4779 869.3414) 
(list 320.4779 869.3517) 
(list 320.4779 869.3619) 
(list 320.4779 869.3722) 
(list 320.4779 869.3825) 
(list 320.4779 869.3928) 
(list 320.4779 869.4031) 
(list 320.4779 869.4133) 
(list 320.4779 869.4236) 
(list 320.4779 869.4339) 
(list 320.4779 869.4442) 
(list 320.4779 869.4544) 
(list 320.4779 869.4647) 
(list 320.4779 869.475) 
(list 320.4779 869.4853) 
(list 320.4779 869.4956) 
(list 320.4779 869.5058) 
(list 320.4779 869.5161) 
(list 320.4779 869.5264) 
(list 320.4779 869.5367) 
(list 320.4779 869.5469) 
(list 320.4779 869.5572) 
(list 320.4779 869.5675) 
(list 320.4779 869.5778) 
(list 320.4779 869.5881) 
(list 320.4779 869.5983) 
(list 320.4779 869.6086) 
(list 320.4779 869.6189) 
(list 320.4779 869.6292) 
(list 320.4779 869.6394) 
(list 320.4779 869.6497) 
(list 320.4779 869.66) 
(list 321.066 869.66)))
(apply 'command (append '("pline") coords '("c")))
(setq tap1 (ssadd (entlast) tap1))
(command "_mirror" (entlast) "" "320,900" "320,901" "No")
(setq tap1 (ssadd (entlast) tap1))
(setq coords (list 
(list 320 869.66) 
(list 320.135 869.66) 
(list 320.135 869.6703) 
(list 320.135 869.6806) 
(list 320.135 869.6908) 
(list 320.135 869.7011) 
(list 320.135 869.7114) 
(list 320.135 869.7217) 
(list 320.135 869.7319) 
(list 320.135 869.7422) 
(list 320.135 869.7525) 
(list 320.135 869.7628) 
(list 320.135 869.7731) 
(list 320.135 869.7833) 
(list 320.135 869.7936) 
(list 320.135 869.8039) 
(list 320.135 869.8142) 
(list 320.135 869.8244) 
(list 320.135 869.8347) 
(list 320.135 869.845) 
(list 320.135 869.8553) 
(list 320.135 869.8656) 
(list 320.135 869.8758) 
(list 320.135 869.8861) 
(list 320.135 869.8964) 
(list 320.135 869.9067) 
(list 320.135 869.9169) 
(list 320.135 869.9272) 
(list 320.135 869.9375) 
(list 320.135 869.9478) 
(list 320.135 869.9581) 
(list 320.135 869.9683) 
(list 320.135 869.9786) 
(list 320.135 869.9889) 
(list 320.135 869.9992) 
(list 320.135 870.0094) 
(list 320.135 870.0197) 
(list 320.135 870.03) 
(list 320 870.03)))
(apply 'command (append '("pline") coords '("c")))
(setq tap1 (ssadd (entlast) tap1))
(command "_mirror" (entlast) "" "320,900" "320,901" "No")
(setq tap1 (ssadd (entlast) tap1))
(setq coords (list 
(list 320.4858 869.66) 
(list 320.4779 869.66) 
(list 320.4772 869.6703) 
(list 320.4744 869.6806) 
(list 320.4698 869.6908) 
(list 320.4634 869.7011) 
(list 320.4554 869.7114) 
(list 320.446 869.7217) 
(list 320.4356 869.7319) 
(list 320.4244 869.7422) 
(list 320.4128 869.7525) 
(list 320.4011 869.7628) 
(list 320.3897 869.7731) 
(list 320.3789 869.7833) 
(list 320.3691 869.7936) 
(list 320.3605 869.8039) 
(list 320.3535 869.8142) 
(list 320.3482 869.8244) 
(list 320.3449 869.8347) 
(list 320.3436 869.845) 
(list 320.3444 869.8553) 
(list 320.3473 869.8656) 
(list 320.3523 869.8758) 
(list 320.3591 869.8861) 
(list 320.3675 869.8964) 
(list 320.3774 869.9067) 
(list 320.3885 869.9169) 
(list 320.4004 869.9272) 
(list 320.4127 869.9375) 
(list 320.4251 869.9478) 
(list 320.4371 869.9581) 
(list 320.4486 869.9683) 
(list 320.459 869.9786) 
(list 320.468 869.9889) 
(list 320.4754 869.9992) 
(list 320.481 870.0094) 
(list 320.4845 870.0197) 
(list 320.4858 870.03) 
(list 320.4858 870.03)))
(apply 'command (append '("pline") coords '("c")))
(setq tap1 (ssadd (entlast) tap1))
(command "_mirror" (entlast) "" "320,900" "320,901" "No")
(setq tap1 (ssadd (entlast) tap1))
(setq coords (list 
(list 321.066 869.66) 
(list 320.4858 869.66) 
(list 320.4858 869.6703) 
(list 320.4858 869.6806) 
(list 320.4858 869.6908) 
(list 320.4858 869.7011) 
(list 320.4858 869.7114) 
(list 320.4858 869.7217) 
(list 320.4858 869.7319) 
(list 320.4858 869.7422) 
(list 320.4858 869.7525) 
(list 320.4858 869.7628) 
(list 320.4858 869.7731) 
(list 320.4858 869.7833) 
(list 320.4858 869.7936) 
(list 320.4858 869.8039) 
(list 320.4858 869.8142) 
(list 320.4858 869.8244) 
(list 320.4858 869.8347) 
(list 320.4858 869.845) 
(list 320.4858 869.8553) 
(list 320.4858 869.8656) 
(list 320.4858 869.8758) 
(list 320.4858 869.8861) 
(list 320.4858 869.8964) 
(list 320.4858 869.9067) 
(list 320.4858 869.9169) 
(list 320.4858 869.9272) 
(list 320.4858 869.9375) 
(list 320.4858 869.9478) 
(list 320.4858 869.9581) 
(list 320.4858 869.9683) 
(list 320.4858 869.9786) 
(list 320.4858 869.9889) 
(list 320.4858 869.9992) 
(list 320.4858 870.0094) 
(list 320.4858 870.0197) 
(list 320.4858 870.03) 
(list 321.066 870.03)))
(apply 'command (append '("pline") coords '("c")))
(setq tap1 (ssadd (entlast) tap1))
(command "_mirror" (entlast) "" "320,900" "320,901" "No")
(setq tap1 (ssadd (entlast) tap1))
(setq coords (list 
(list 320 870.03) 
(list 320.135 870.03) 
(list 320.135 870.0403) 
(list 320.135 870.0506) 
(list 320.135 870.0608) 
(list 320.135 870.0711) 
(list 320.135 870.0814) 
(list 320.135 870.0917) 
(list 320.135 870.1019) 
(list 320.135 870.1122) 
(list 320.135 870.1225) 
(list 320.135 870.1328) 
(list 320.135 870.1431) 
(list 320.135 870.1533) 
(list 320.135 870.1636) 
(list 320.135 870.1739) 
(list 320.135 870.1842) 
(list 320.135 870.1944) 
(list 320.135 870.2047) 
(list 320.135 870.215) 
(list 320.135 870.2253) 
(list 320.135 870.2356) 
(list 320.135 870.2458) 
(list 320.135 870.2561) 
(list 320.135 870.2664) 
(list 320.135 870.2767) 
(list 320.135 870.2869) 
(list 320.135 870.2972) 
(list 320.135 870.3075) 
(list 320.135 870.3178) 
(list 320.135 870.3281) 
(list 320.135 870.3383) 
(list 320.135 870.3486) 
(list 320.135 870.3589) 
(list 320.135 870.3692) 
(list 320.135 870.3794) 
(list 320.135 870.3897) 
(list 320.135 870.4) 
(list 320 870.4)))
(apply 'command (append '("pline") coords '("c")))
(setq tap1 (ssadd (entlast) tap1))
(command "_mirror" (entlast) "" "320,900" "320,901" "No")
(setq tap1 (ssadd (entlast) tap1))
(setq coords (list 
(list 320.4937 870.03) 
(list 320.4858 870.03) 
(list 320.4849 870.0403) 
(list 320.4818 870.0506) 
(list 320.4766 870.0608) 
(list 320.4693 870.0711) 
(list 320.4603 870.0814) 
(list 320.4498 870.0917) 
(list 320.4381 870.1019) 
(list 320.4256 870.1122) 
(list 320.4125 870.1225) 
(list 320.3994 870.1328) 
(list 320.3866 870.1431) 
(list 320.3746 870.1533) 
(list 320.3636 870.1636) 
(list 320.354 870.1739) 
(list 320.3462 870.1842) 
(list 320.3403 870.1944) 
(list 320.3366 870.2047) 
(list 320.3352 870.215) 
(list 320.3361 870.2253) 
(list 320.3394 870.2356) 
(list 320.3449 870.2458) 
(list 320.3526 870.2561) 
(list 320.362 870.2664) 
(list 320.3731 870.2767) 
(list 320.3854 870.2869) 
(list 320.3987 870.2972) 
(list 320.4124 870.3075) 
(list 320.4262 870.3178) 
(list 320.4397 870.3281) 
(list 320.4524 870.3383) 
(list 320.4639 870.3486) 
(list 320.474 870.3589) 
(list 320.4822 870.3692) 
(list 320.4884 870.3794) 
(list 320.4922 870.3897) 
(list 320.4937 870.4) 
(list 320.4937 870.4)))
(apply 'command (append '("pline") coords '("c")))
(setq tap1 (ssadd (entlast) tap1))
(command "_mirror" (entlast) "" "320,900" "320,901" "No")
(setq tap1 (ssadd (entlast) tap1))
(setq coords (list 
(list 321.066 870.03) 
(list 320.4937 870.03) 
(list 320.4937 870.0403) 
(list 320.4937 870.0506) 
(list 320.4937 870.0608) 
(list 320.4937 870.0711) 
(list 320.4937 870.0814) 
(list 320.4937 870.0917) 
(list 320.4937 870.1019) 
(list 320.4937 870.1122) 
(list 320.4937 870.1225) 
(list 320.4937 870.1328) 
(list 320.4937 870.1431) 
(list 320.4937 870.1533) 
(list 320.4937 870.1636) 
(list 320.4937 870.1739) 
(list 320.4937 870.1842) 
(list 320.4937 870.1944) 
(list 320.4937 870.2047) 
(list 320.4937 870.215) 
(list 320.4937 870.2253) 
(list 320.4937 870.2356) 
(list 320.4937 870.2458) 
(list 320.4937 870.2561) 
(list 320.4937 870.2664) 
(list 320.4937 870.2767) 
(list 320.4937 870.2869) 
(list 320.4937 870.2972) 
(list 320.4937 870.3075) 
(list 320.4937 870.3178) 
(list 320.4937 870.3281) 
(list 320.4937 870.3383) 
(list 320.4937 870.3486) 
(list 320.4937 870.3589) 
(list 320.4937 870.3692) 
(list 320.4937 870.3794) 
(list 320.4937 870.3897) 
(list 320.4937 870.4) 
(list 321.066 870.4)))
(apply 'command (append '("pline") coords '("c")))
(setq tap1 (ssadd (entlast) tap1))
(command "_mirror" (entlast) "" "320,900" "320,901" "No")
(setq tap1 (ssadd (entlast) tap1))
(setq coords (list 
(list 320 870.4) 
(list 320.135 870.4) 
(list 320.135 870.4103) 
(list 320.135 870.4206) 
(list 320.135 870.4308) 
(list 320.135 870.4411) 
(list 320.135 870.4514) 
(list 320.135 870.4617) 
(list 320.135 870.4719) 
(list 320.135 870.4822) 
(list 320.135 870.4925) 
(list 320.135 870.5028) 
(list 320.135 870.5131) 
(list 320.135 870.5233) 
(list 320.135 870.5336) 
(list 320.135 870.5439) 
(list 320.135 870.5542) 
(list 320.135 870.5644) 
(list 320.135 870.5747) 
(list 320.135 870.585) 
(list 320.135 870.5953) 
(list 320.135 870.6056) 
(list 320.135 870.6158) 
(list 320.135 870.6261) 
(list 320.135 870.6364) 
(list 320.135 870.6467) 
(list 320.135 870.6569) 
(list 320.135 870.6672) 
(list 320.135 870.6775) 
(list 320.135 870.6878) 
(list 320.135 870.6981) 
(list 320.135 870.7083) 
(list 320.135 870.7186) 
(list 320.135 870.7289) 
(list 320.135 870.7392) 
(list 320.135 870.7494) 
(list 320.135 870.7597) 
(list 320.135 870.77) 
(list 320 870.77)))
(apply 'command (append '("pline") coords '("c")))
(setq tap1 (ssadd (entlast) tap1))
(command "_mirror" (entlast) "" "320,900" "320,901" "No")
(setq tap1 (ssadd (entlast) tap1))
(setq coords (list 
(list 320.5015 870.4) 
(list 320.4937 870.4) 
(list 320.4926 870.4103) 
(list 320.4892 870.4206) 
(list 320.4833 870.4308) 
(list 320.4753 870.4411) 
(list 320.4653 870.4514) 
(list 320.4536 870.4617) 
(list 320.4406 870.4719) 
(list 320.4267 870.4822) 
(list 320.4123 870.4925) 
(list 320.3977 870.5028) 
(list 320.3836 870.5131) 
(list 320.3702 870.5233) 
(list 320.3581 870.5336) 
(list 320.3475 870.5439) 
(list 320.3389 870.5542) 
(list 320.3324 870.5644) 
(list 320.3283 870.5747) 
(list 320.3268 870.585) 
(list 320.3279 870.5953) 
(list 320.3315 870.6056) 
(list 320.3376 870.6158) 
(list 320.3461 870.6261) 
(list 320.3565 870.6364) 
(list 320.3688 870.6467) 
(list 320.3824 870.6569) 
(list 320.397 870.6672) 
(list 320.4121 870.6775) 
(list 320.4273 870.6878) 
(list 320.4422 870.6981) 
(list 320.4562 870.7083) 
(list 320.4689 870.7186) 
(list 320.4799 870.7289) 
(list 320.489 870.7392) 
(list 320.4957 870.7494) 
(list 320.5 870.7597) 
(list 320.5015 870.77) 
(list 320.5015 870.77)))
(apply 'command (append '("pline") coords '("c")))
(setq tap1 (ssadd (entlast) tap1))
(command "_mirror" (entlast) "" "320,900" "320,901" "No")
(setq tap1 (ssadd (entlast) tap1))
(setq coords (list 
(list 321.066 870.4) 
(list 320.5015 870.4) 
(list 320.5015 870.4103) 
(list 320.5015 870.4206) 
(list 320.5015 870.4308) 
(list 320.5015 870.4411) 
(list 320.5015 870.4514) 
(list 320.5015 870.4617) 
(list 320.5015 870.4719) 
(list 320.5015 870.4822) 
(list 320.5015 870.4925) 
(list 320.5015 870.5028) 
(list 320.5015 870.5131) 
(list 320.5015 870.5233) 
(list 320.5015 870.5336) 
(list 320.5015 870.5439) 
(list 320.5015 870.5542) 
(list 320.5015 870.5644) 
(list 320.5015 870.5747) 
(list 320.5015 870.585) 
(list 320.5015 870.5953) 
(list 320.5015 870.6056) 
(list 320.5015 870.6158) 
(list 320.5015 870.6261) 
(list 320.5015 870.6364) 
(list 320.5015 870.6467) 
(list 320.5015 870.6569) 
(list 320.5015 870.6672) 
(list 320.5015 870.6775) 
(list 320.5015 870.6878) 
(list 320.5015 870.6981) 
(list 320.5015 870.7083) 
(list 320.5015 870.7186) 
(list 320.5015 870.7289) 
(list 320.5015 870.7392) 
(list 320.5015 870.7494) 
(list 320.5015 870.7597) 
(list 320.5015 870.77) 
(list 321.066 870.77)))
(apply 'command (append '("pline") coords '("c")))
(setq tap1 (ssadd (entlast) tap1))
(command "_mirror" (entlast) "" "320,900" "320,901" "No")
(setq tap1 (ssadd (entlast) tap1))
(setq coords (list 
(list 320 870.77) 
(list 320.135 870.77) 
(list 320.135 870.7803) 
(list 320.135 870.7906) 
(list 320.135 870.8008) 
(list 320.135 870.8111) 
(list 320.135 870.8214) 
(list 320.135 870.8317) 
(list 320.135 870.8419) 
(list 320.135 870.8522) 
(list 320.135 870.8625) 
(list 320.135 870.8728) 
(list 320.135 870.8831) 
(list 320.135 870.8933) 
(list 320.135 870.9036) 
(list 320.135 870.9139) 
(list 320.135 870.9242) 
(list 320.135 870.9344) 
(list 320.135 870.9447) 
(list 320.135 870.955) 
(list 320.135 870.9653) 
(list 320.135 870.9756) 
(list 320.135 870.9858) 
(list 320.135 870.9961) 
(list 320.135 871.0064) 
(list 320.135 871.0167) 
(list 320.135 871.0269) 
(list 320.135 871.0372) 
(list 320.135 871.0475) 
(list 320.135 871.0578) 
(list 320.135 871.0681) 
(list 320.135 871.0783) 
(list 320.135 871.0886) 
(list 320.135 871.0989) 
(list 320.135 871.1092) 
(list 320.135 871.1194) 
(list 320.135 871.1297) 
(list 320.135 871.14) 
(list 320 871.14)))
(apply 'command (append '("pline") coords '("c")))
(setq tap1 (ssadd (entlast) tap1))
(command "_mirror" (entlast) "" "320,900" "320,901" "No")
(setq tap1 (ssadd (entlast) tap1))
(setq coords (list 
(list 320.5094 870.77) 
(list 320.5015 870.77) 
(list 320.5004 870.7803) 
(list 320.4965 870.7906) 
(list 320.4901 870.8008) 
(list 320.4813 870.8111) 
(list 320.4703 870.8214) 
(list 320.4574 870.8317) 
(list 320.4432 870.8419) 
(list 320.4279 870.8522) 
(list 320.412 870.8625) 
(list 320.3961 870.8728) 
(list 320.3805 870.8831) 
(list 320.3659 870.8933) 
(list 320.3526 870.9036) 
(list 320.341 870.9139) 
(list 320.3315 870.9242) 
(list 320.3245 870.9344) 
(list 320.3201 870.9447) 
(list 320.3184 870.955) 
(list 320.3196 870.9653) 
(list 320.3236 870.9756) 
(list 320.3303 870.9858) 
(list 320.3396 870.9961) 
(list 320.351 871.0064) 
(list 320.3644 871.0167) 
(list 320.3793 871.0269) 
(list 320.3953 871.0372) 
(list 320.4119 871.0475) 
(list 320.4285 871.0578) 
(list 320.4447 871.0681) 
(list 320.46 871.0783) 
(list 320.4738 871.0886) 
(list 320.4859 871.0989) 
(list 320.4958 871.1092) 
(list 320.5031 871.1194) 
(list 320.5077 871.1297) 
(list 320.5094 871.14) 
(list 320.5094 871.14)))
(apply 'command (append '("pline") coords '("c")))
(setq tap1 (ssadd (entlast) tap1))
(command "_mirror" (entlast) "" "320,900" "320,901" "No")
(setq tap1 (ssadd (entlast) tap1))
(setq coords (list 
(list 321.066 870.77) 
(list 320.5094 870.77) 
(list 320.5094 870.7803) 
(list 320.5094 870.7906) 
(list 320.5094 870.8008) 
(list 320.5094 870.8111) 
(list 320.5094 870.8214) 
(list 320.5094 870.8317) 
(list 320.5094 870.8419) 
(list 320.5094 870.8522) 
(list 320.5094 870.8625) 
(list 320.5094 870.8728) 
(list 320.5094 870.8831) 
(list 320.5094 870.8933) 
(list 320.5094 870.9036) 
(list 320.5094 870.9139) 
(list 320.5094 870.9242) 
(list 320.5094 870.9344) 
(list 320.5094 870.9447) 
(list 320.5094 870.955) 
(list 320.5094 870.9653) 
(list 320.5094 870.9756) 
(list 320.5094 870.9858) 
(list 320.5094 870.9961) 
(list 320.5094 871.0064) 
(list 320.5094 871.0167) 
(list 320.5094 871.0269) 
(list 320.5094 871.0372) 
(list 320.5094 871.0475) 
(list 320.5094 871.0578) 
(list 320.5094 871.0681) 
(list 320.5094 871.0783) 
(list 320.5094 871.0886) 
(list 320.5094 871.0989) 
(list 320.5094 871.1092) 
(list 320.5094 871.1194) 
(list 320.5094 871.1297) 
(list 320.5094 871.14) 
(list 321.066 871.14)))
(apply 'command (append '("pline") coords '("c")))
(setq tap1 (ssadd (entlast) tap1))
(command "_mirror" (entlast) "" "320,900" "320,901" "No")
(setq tap1 (ssadd (entlast) tap1))
(setq coords (list 
(list 320 871.14) 
(list 320.135 871.14) 
(list 320.135 871.1503) 
(list 320.135 871.1606) 
(list 320.135 871.1708) 
(list 320.135 871.1811) 
(list 320.135 871.1914) 
(list 320.135 871.2017) 
(list 320.135 871.2119) 
(list 320.135 871.2222) 
(list 320.135 871.2325) 
(list 320.135 871.2428) 
(list 320.135 871.2531) 
(list 320.135 871.2633) 
(list 320.135 871.2736) 
(list 320.135 871.2839) 
(list 320.135 871.2942) 
(list 320.135 871.3044) 
(list 320.135 871.3147) 
(list 320.135 871.325) 
(list 320.135 871.3353) 
(list 320.135 871.3456) 
(list 320.135 871.3558) 
(list 320.135 871.3661) 
(list 320.135 871.3764) 
(list 320.135 871.3867) 
(list 320.135 871.3969) 
(list 320.135 871.4072) 
(list 320.135 871.4175) 
(list 320.135 871.4278) 
(list 320.135 871.4381) 
(list 320.135 871.4483) 
(list 320.135 871.4586) 
(list 320.135 871.4689) 
(list 320.135 871.4792) 
(list 320.135 871.4894) 
(list 320.135 871.4997) 
(list 320.135 871.51) 
(list 320 871.51)))
(apply 'command (append '("pline") coords '("c")))
(setq tap1 (ssadd (entlast) tap1))
(command "_mirror" (entlast) "" "320,900" "320,901" "No")
(setq tap1 (ssadd (entlast) tap1))
(setq coords (list 
(list 320.5173 871.14) 
(list 320.5094 871.14) 
(list 320.5081 871.1503) 
(list 320.5039 871.1606) 
(list 320.4969 871.1708) 
(list 320.4872 871.1811) 
(list 320.4752 871.1914) 
(list 320.4612 871.2017) 
(list 320.4457 871.2119) 
(list 320.429 871.2222) 
(list 320.4117 871.2325) 
(list 320.3944 871.2428) 
(list 320.3775 871.2531) 
(list 320.3616 871.2633) 
(list 320.3471 871.2736) 
(list 320.3345 871.2839) 
(list 320.3242 871.2942) 
(list 320.3166 871.3044) 
(list 320.3118 871.3147) 
(list 320.31 871.325) 
(list 320.3113 871.3353) 
(list 320.3157 871.3456) 
(list 320.323 871.3558) 
(list 320.3331 871.3661) 
(list 320.3456 871.3764) 
(list 320.3601 871.3867) 
(list 320.3763 871.3969) 
(list 320.3936 871.4072) 
(list 320.4116 871.4175) 
(list 320.4296 871.4278) 
(list 320.4472 871.4381) 
(list 320.4638 871.4483) 
(list 320.4788 871.4586) 
(list 320.4919 871.4689) 
(list 320.5025 871.4792) 
(list 320.5105 871.4894) 
(list 320.5154 871.4997) 
(list 320.5173 871.51) 
(list 320.5173 871.51)))
(apply 'command (append '("pline") coords '("c")))
(setq tap1 (ssadd (entlast) tap1))
(command "_mirror" (entlast) "" "320,900" "320,901" "No")
(setq tap1 (ssadd (entlast) tap1))
(setq coords (list 
(list 321.066 871.14) 
(list 320.5173 871.14) 
(list 320.5173 871.1503) 
(list 320.5173 871.1606) 
(list 320.5173 871.1708) 
(list 320.5173 871.1811) 
(list 320.5173 871.1914) 
(list 320.5173 871.2017) 
(list 320.5173 871.2119) 
(list 320.5173 871.2222) 
(list 320.5173 871.2325) 
(list 320.5173 871.2428) 
(list 320.5173 871.2531) 
(list 320.5173 871.2633) 
(list 320.5173 871.2736) 
(list 320.5173 871.2839) 
(list 320.5173 871.2942) 
(list 320.5173 871.3044) 
(list 320.5173 871.3147) 
(list 320.5173 871.325) 
(list 320.5173 871.3353) 
(list 320.5173 871.3456) 
(list 320.5173 871.3558) 
(list 320.5173 871.3661) 
(list 320.5173 871.3764) 
(list 320.5173 871.3867) 
(list 320.5173 871.3969) 
(list 320.5173 871.4072) 
(list 320.5173 871.4175) 
(list 320.5173 871.4278) 
(list 320.5173 871.4381) 
(list 320.5173 871.4483) 
(list 320.5173 871.4586) 
(list 320.5173 871.4689) 
(list 320.5173 871.4792) 
(list 320.5173 871.4894) 
(list 320.5173 871.4997) 
(list 320.5173 871.51) 
(list 321.066 871.51)))
(apply 'command (append '("pline") coords '("c")))
(setq tap1 (ssadd (entlast) tap1))
(command "_mirror" (entlast) "" "320,900" "320,901" "No")
(setq tap1 (ssadd (entlast) tap1))
(setq coords (list 
(list 320 871.51) 
(list 320.135 871.51) 
(list 320.135 871.5203) 
(list 320.135 871.5306) 
(list 320.135 871.5408) 
(list 320.135 871.5511) 
(list 320.135 871.5614) 
(list 320.135 871.5717) 
(list 320.135 871.5819) 
(list 320.135 871.5922) 
(list 320.135 871.6025) 
(list 320.135 871.6128) 
(list 320.135 871.6231) 
(list 320.135 871.6333) 
(list 320.135 871.6436) 
(list 320.135 871.6539) 
(list 320.135 871.6642) 
(list 320.135 871.6744) 
(list 320.135 871.6847) 
(list 320.135 871.695) 
(list 320.135 871.7053) 
(list 320.135 871.7156) 
(list 320.135 871.7258) 
(list 320.135 871.7361) 
(list 320.135 871.7464) 
(list 320.135 871.7567) 
(list 320.135 871.7669) 
(list 320.135 871.7772) 
(list 320.135 871.7875) 
(list 320.135 871.7978) 
(list 320.135 871.8081) 
(list 320.135 871.8183) 
(list 320.135 871.8286) 
(list 320.135 871.8389) 
(list 320.135 871.8492) 
(list 320.135 871.8594) 
(list 320.135 871.8697) 
(list 320.135 871.88) 
(list 320 871.88)))
(apply 'command (append '("pline") coords '("c")))
(setq tap1 (ssadd (entlast) tap1))
(command "_mirror" (entlast) "" "320,900" "320,901" "No")
(setq tap1 (ssadd (entlast) tap1))
(setq coords (list 
(list 320.5251 871.51) 
(list 320.5173 871.51) 
(list 320.5159 871.5203) 
(list 320.5113 871.5306) 
(list 320.5037 871.5408) 
(list 320.4932 871.5511) 
(list 320.4802 871.5614) 
(list 320.465 871.5717) 
(list 320.4482 871.5819) 
(list 320.4301 871.5922) 
(list 320.4115 871.6025) 
(list 320.3927 871.6128) 
(list 320.3744 871.6231) 
(list 320.3572 871.6333) 
(list 320.3416 871.6436) 
(list 320.328 871.6539) 
(list 320.3169 871.6642) 
(list 320.3087 871.6744) 
(list 320.3035 871.6847) 
(list 320.3016 871.695) 
(list 320.303 871.7053) 
(list 320.3078 871.7156) 
(list 320.3157 871.7258) 
(list 320.3266 871.7361) 
(list 320.3401 871.7464) 
(list 320.3558 871.7567) 
(list 320.3733 871.7669) 
(list 320.392 871.7772) 
(list 320.4113 871.7875) 
(list 320.4308 871.7978) 
(list 320.4497 871.8081) 
(list 320.4676 871.8183) 
(list 320.4838 871.8286) 
(list 320.4978 871.8389) 
(list 320.5093 871.8492) 
(list 320.5179 871.8594) 
(list 320.5232 871.8697) 
(list 320.5251 871.88) 
(list 320.5251 871.88)))
(apply 'command (append '("pline") coords '("c")))
(setq tap1 (ssadd (entlast) tap1))
(command "_mirror" (entlast) "" "320,900" "320,901" "No")
(setq tap1 (ssadd (entlast) tap1))
(setq coords (list 
(list 321.066 871.51) 
(list 320.5251 871.51) 
(list 320.5251 871.5203) 
(list 320.5251 871.5306) 
(list 320.5251 871.5408) 
(list 320.5251 871.5511) 
(list 320.5251 871.5614) 
(list 320.5251 871.5717) 
(list 320.5251 871.5819) 
(list 320.5251 871.5922) 
(list 320.5251 871.6025) 
(list 320.5251 871.6128) 
(list 320.5251 871.6231) 
(list 320.5251 871.6333) 
(list 320.5251 871.6436) 
(list 320.5251 871.6539) 
(list 320.5251 871.6642) 
(list 320.5251 871.6744) 
(list 320.5251 871.6847) 
(list 320.5251 871.695) 
(list 320.5251 871.7053) 
(list 320.5251 871.7156) 
(list 320.5251 871.7258) 
(list 320.5251 871.7361) 
(list 320.5251 871.7464) 
(list 320.5251 871.7567) 
(list 320.5251 871.7669) 
(list 320.5251 871.7772) 
(list 320.5251 871.7875) 
(list 320.5251 871.7978) 
(list 320.5251 871.8081) 
(list 320.5251 871.8183) 
(list 320.5251 871.8286) 
(list 320.5251 871.8389) 
(list 320.5251 871.8492) 
(list 320.5251 871.8594) 
(list 320.5251 871.8697) 
(list 320.5251 871.88) 
(list 321.066 871.88)))
(apply 'command (append '("pline") coords '("c")))
(setq tap1 (ssadd (entlast) tap1))
(command "_mirror" (entlast) "" "320,900" "320,901" "No")
(setq tap1 (ssadd (entlast) tap1))
(setq coords (list 
(list 320 871.88) 
(list 320.135 871.88) 
(list 320.135 871.8903) 
(list 320.135 871.9006) 
(list 320.135 871.9108) 
(list 320.135 871.9211) 
(list 320.135 871.9314) 
(list 320.135 871.9417) 
(list 320.135 871.9519) 
(list 320.135 871.9622) 
(list 320.135 871.9725) 
(list 320.135 871.9828) 
(list 320.135 871.9931) 
(list 320.135 872.0033) 
(list 320.135 872.0136) 
(list 320.135 872.0239) 
(list 320.135 872.0342) 
(list 320.135 872.0444) 
(list 320.135 872.0547) 
(list 320.135 872.065) 
(list 320.135 872.0753) 
(list 320.135 872.0856) 
(list 320.135 872.0958) 
(list 320.135 872.1061) 
(list 320.135 872.1164) 
(list 320.135 872.1267) 
(list 320.135 872.1369) 
(list 320.135 872.1472) 
(list 320.135 872.1575) 
(list 320.135 872.1678) 
(list 320.135 872.1781) 
(list 320.135 872.1883) 
(list 320.135 872.1986) 
(list 320.135 872.2089) 
(list 320.135 872.2192) 
(list 320.135 872.2294) 
(list 320.135 872.2397) 
(list 320.135 872.25) 
(list 320 872.25)))
(apply 'command (append '("pline") coords '("c")))
(setq tap1 (ssadd (entlast) tap1))
(command "_mirror" (entlast) "" "320,900" "320,901" "No")
(setq tap1 (ssadd (entlast) tap1))
(setq coords (list 
(list 320.533 871.88) 
(list 320.5251 871.88) 
(list 320.5236 871.8903) 
(list 320.5187 871.9006) 
(list 320.5104 871.9108) 
(list 320.4992 871.9211) 
(list 320.4851 871.9314) 
(list 320.4688 871.9417) 
(list 320.4507 871.9519) 
(list 320.4313 871.9622) 
(list 320.4112 871.9725) 
(list 320.391 871.9828) 
(list 320.3714 871.9931) 
(list 320.3529 872.0033) 
(list 320.3361 872.0136) 
(list 320.3215 872.0239) 
(list 320.3096 872.0342) 
(list 320.3008 872.0444) 
(list 320.2952 872.0547) 
(list 320.2932 872.065) 
(list 320.2948 872.0753) 
(list 320.2999 872.0856) 
(list 320.3084 872.0958) 
(list 320.3201 872.1061) 
(list 320.3346 872.1164) 
(list 320.3514 872.1267) 
(list 320.3702 872.1369) 
(list 320.3903 872.1472) 
(list 320.4111 872.1575) 
(list 320.4319 872.1678) 
(list 320.4522 872.1781) 
(list 320.4714 872.1883) 
(list 320.4887 872.1986) 
(list 320.5038 872.2089) 
(list 320.5161 872.2192) 
(list 320.5252 872.2294) 
(list 320.5309 872.2397) 
(list 320.533 872.25) 
(list 320.533 872.25)))
(apply 'command (append '("pline") coords '("c")))
(setq tap1 (ssadd (entlast) tap1))
(command "_mirror" (entlast) "" "320,900" "320,901" "No")
(setq tap1 (ssadd (entlast) tap1))
(setq coords (list 
(list 321.066 871.88) 
(list 320.533 871.88) 
(list 320.533 871.8903) 
(list 320.533 871.9006) 
(list 320.533 871.9108) 
(list 320.533 871.9211) 
(list 320.533 871.9314) 
(list 320.533 871.9417) 
(list 320.533 871.9519) 
(list 320.533 871.9622) 
(list 320.533 871.9725) 
(list 320.533 871.9828) 
(list 320.533 871.9931) 
(list 320.533 872.0033) 
(list 320.533 872.0136) 
(list 320.533 872.0239) 
(list 320.533 872.0342) 
(list 320.533 872.0444) 
(list 320.533 872.0547) 
(list 320.533 872.065) 
(list 320.533 872.0753) 
(list 320.533 872.0856) 
(list 320.533 872.0958) 
(list 320.533 872.1061) 
(list 320.533 872.1164) 
(list 320.533 872.1267) 
(list 320.533 872.1369) 
(list 320.533 872.1472) 
(list 320.533 872.1575) 
(list 320.533 872.1678) 
(list 320.533 872.1781) 
(list 320.533 872.1883) 
(list 320.533 872.1986) 
(list 320.533 872.2089) 
(list 320.533 872.2192) 
(list 320.533 872.2294) 
(list 320.533 872.2397) 
(list 320.533 872.25) 
(list 321.066 872.25)))
(apply 'command (append '("pline") coords '("c")))
(setq tap1 (ssadd (entlast) tap1))
(command "_mirror" (entlast) "" "320,900" "320,901" "No")
(setq tap1 (ssadd (entlast) tap1))
(command "_block" "blktap1" "320,900" tap1 "")
(command "_insert" "blktap1" "320,900" "1" "1" "0")
(command "_insert" "blktap1" "320,900" "1" "1" "180")
(setq uc1 nil)
(setq uc1 (ssadd))
(setq coords (list 
(list 0 -0.185) 
(list 0.135 -0.185) 
(list 0.135 -0.17472) 
(list 0.135 -0.16444) 
(list 0.135 -0.15417) 
(list 0.135 -0.14389) 
(list 0.135 -0.13361) 
(list 0.135 -0.12333) 
(list 0.135 -0.11306) 
(list 0.135 -0.10278) 
(list 0.135 -0.0925) 
(list 0.135 -0.082222) 
(list 0.135 -0.071944) 
(list 0.135 -0.061667) 
(list 0.135 -0.051389) 
(list 0.135 -0.041111) 
(list 0.135 -0.030833) 
(list 0.135 -0.020556) 
(list 0.135 -0.010278) 
(list 0.135 0) 
(list 0.135 0.010278) 
(list 0.135 0.020556) 
(list 0.135 0.030833) 
(list 0.135 0.041111) 
(list 0.135 0.051389) 
(list 0.135 0.061667) 
(list 0.135 0.071944) 
(list 0.135 0.082222) 
(list 0.135 0.0925) 
(list 0.135 0.10278) 
(list 0.135 0.11306) 
(list 0.135 0.12333) 
(list 0.135 0.13361) 
(list 0.135 0.14389) 
(list 0.135 0.15417) 
(list 0.135 0.16444) 
(list 0.135 0.17472) 
(list 0.135 0.185) 
(list 0 0.185)))
(apply 'command (append '("pline") coords '("c")))
(setq uc1 (ssadd (entlast) uc1))
(setq coords (list 
(list 1.066 -0.185) 
(list 0.533 -0.185) 
(list 0.53115 -0.17472) 
(list 0.52564 -0.16444) 
(list 0.51665 -0.15417) 
(list 0.50446 -0.14389) 
(list 0.48942 -0.13361) 
(list 0.472 -0.12333) 
(list 0.45273 -0.11306) 
(list 0.43218 -0.10278) 
(list 0.411 -0.0925) 
(list 0.38982 -0.082222) 
(list 0.36927 -0.071944) 
(list 0.35 -0.061667) 
(list 0.33258 -0.051389) 
(list 0.31754 -0.041111) 
(list 0.30534 -0.030833) 
(list 0.29636 -0.020556) 
(list 0.29085 -0.010278) 
(list 0.289 0) 
(list 0.29085 0.010278) 
(list 0.29636 0.020556) 
(list 0.30534 0.030833) 
(list 0.31754 0.041111) 
(list 0.33258 0.051389) 
(list 0.35 0.061667) 
(list 0.36927 0.071944) 
(list 0.38982 0.082222) 
(list 0.411 0.0925) 
(list 0.43218 0.10278) 
(list 0.45273 0.11306) 
(list 0.472 0.12333) 
(list 0.48942 0.13361) 
(list 0.50446 0.14389) 
(list 0.51665 0.15417) 
(list 0.52564 0.16444) 
(list 0.53115 0.17472) 
(list 0.533 0.185) 
(list 1.066 0.185)))
(apply 'command (append '("pline") coords '("c")))
(setq uc1 (ssadd (entlast) uc1))
(command "_block" "blkuc1" "0,0.185" uc1 "")
(command "_insert" "blkuc1" "320,872.62" "1" "1" "0")
(command "_insert" "blkuc1" "320,872.25" "1" "1" "180")
(command "_insert" "blkuc1" "320,872.99" "1" "1" "0")
(command "_insert" "blkuc1" "320,872.62" "1" "1" "180")
(command "_insert" "blkuc1" "320,873.36" "1" "1" "0")
(command "_insert" "blkuc1" "320,872.99" "1" "1" "180")
(command "_insert" "blkuc1" "320,873.73" "1" "1" "0")
(command "_insert" "blkuc1" "320,873.36" "1" "1" "180")
(command "_insert" "blkuc1" "320,874.1" "1" "1" "0")
(command "_insert" "blkuc1" "320,873.73" "1" "1" "180")
(command "_insert" "blkuc1" "320,874.47" "1" "1" "0")
(command "_insert" "blkuc1" "320,874.1" "1" "1" "180")
(command "_insert" "blkuc1" "320,874.84" "1" "1" "0")
(command "_insert" "blkuc1" "320,874.47" "1" "1" "180")
(command "_insert" "blkuc1" "320,875.21" "1" "1" "0")
(command "_insert" "blkuc1" "320,874.84" "1" "1" "180")
(command "_insert" "blkuc1" "320,875.58" "1" "1" "0")
(command "_insert" "blkuc1" "320,875.21" "1" "1" "180")
(command "_insert" "blkuc1" "320,875.95" "1" "1" "0")
(command "_insert" "blkuc1" "320,875.58" "1" "1" "180")
(command "_insert" "blkuc1" "320,876.32" "1" "1" "0")
(command "_insert" "blkuc1" "320,875.95" "1" "1" "180")
(command "_insert" "blkuc1" "320,876.69" "1" "1" "0")
(command "_insert" "blkuc1" "320,876.32" "1" "1" "180")
(command "_insert" "blkuc1" "320,877.06" "1" "1" "0")
(command "_insert" "blkuc1" "320,876.69" "1" "1" "180")
(command "_insert" "blkuc1" "320,877.43" "1" "1" "0")
(command "_insert" "blkuc1" "320,877.06" "1" "1" "180")
(command "_insert" "blkuc1" "320,877.8" "1" "1" "0")
(command "_insert" "blkuc1" "320,877.43" "1" "1" "180")
(command "_insert" "blkuc1" "320,878.17" "1" "1" "0")
(command "_insert" "blkuc1" "320,877.8" "1" "1" "180")
(command "_insert" "blkuc1" "320,878.54" "1" "1" "0")
(command "_insert" "blkuc1" "320,878.17" "1" "1" "180")
(command "_insert" "blkuc1" "320,878.91" "1" "1" "0")
(command "_insert" "blkuc1" "320,878.54" "1" "1" "180")
(command "_insert" "blkuc1" "320,879.28" "1" "1" "0")
(command "_insert" "blkuc1" "320,878.91" "1" "1" "180")
(command "_insert" "blkuc1" "320,879.65" "1" "1" "0")
(command "_insert" "blkuc1" "320,879.28" "1" "1" "180")
(command "_insert" "blkuc1" "320,880.02" "1" "1" "0")
(command "_insert" "blkuc1" "320,879.65" "1" "1" "180")
(command "_insert" "blkuc1" "320,880.39" "1" "1" "0")
(command "_insert" "blkuc1" "320,880.02" "1" "1" "180")
(command "_insert" "blkuc1" "320,880.76" "1" "1" "0")
(command "_insert" "blkuc1" "320,880.39" "1" "1" "180")
(command "_insert" "blkuc1" "320,881.13" "1" "1" "0")
(command "_insert" "blkuc1" "320,880.76" "1" "1" "180")
(command "_insert" "blkuc1" "320,881.5" "1" "1" "0")
(command "_insert" "blkuc1" "320,881.13" "1" "1" "180")
(command "_insert" "blkuc1" "320,881.87" "1" "1" "0")
(command "_insert" "blkuc1" "320,881.5" "1" "1" "180")
(command "_insert" "blkuc1" "320,882.24" "1" "1" "0")
(command "_insert" "blkuc1" "320,881.87" "1" "1" "180")
(command "_insert" "blkuc1" "320,882.61" "1" "1" "0")
(command "_insert" "blkuc1" "320,882.24" "1" "1" "180")
(command "_insert" "blkuc1" "320,882.98" "1" "1" "0")
(command "_insert" "blkuc1" "320,882.61" "1" "1" "180")
(command "_insert" "blkuc1" "320,883.35" "1" "1" "0")
(command "_insert" "blkuc1" "320,882.98" "1" "1" "180")
(command "_insert" "blkuc1" "320,883.72" "1" "1" "0")
(command "_insert" "blkuc1" "320,883.35" "1" "1" "180")
(command "_insert" "blkuc1" "320,884.09" "1" "1" "0")
(command "_insert" "blkuc1" "320,883.72" "1" "1" "180")
(command "_insert" "blkuc1" "320,884.46" "1" "1" "0")
(command "_insert" "blkuc1" "320,884.09" "1" "1" "180")
(command "_insert" "blkuc1" "320,884.83" "1" "1" "0")
(command "_insert" "blkuc1" "320,884.46" "1" "1" "180")
(command "_insert" "blkuc1" "320,885.2" "1" "1" "0")
(command "_insert" "blkuc1" "320,884.83" "1" "1" "180")
(command "_insert" "blkuc1" "320,885.57" "1" "1" "0")
(command "_insert" "blkuc1" "320,885.2" "1" "1" "180")
(command "_insert" "blkuc1" "320,885.94" "1" "1" "0")
(command "_insert" "blkuc1" "320,885.57" "1" "1" "180")
(command "_insert" "blkuc1" "320,886.31" "1" "1" "0")
(command "_insert" "blkuc1" "320,885.94" "1" "1" "180")
(command "_insert" "blkuc1" "320,886.68" "1" "1" "0")
(command "_insert" "blkuc1" "320,886.31" "1" "1" "180")
(command "_insert" "blkuc1" "320,887.05" "1" "1" "0")
(command "_insert" "blkuc1" "320,886.68" "1" "1" "180")
(command "_insert" "blkuc1" "320,887.42" "1" "1" "0")
(command "_insert" "blkuc1" "320,887.05" "1" "1" "180")
(command "_insert" "blkuc1" "320,887.79" "1" "1" "0")
(command "_insert" "blkuc1" "320,887.42" "1" "1" "180")
(command "_insert" "blkuc1" "320,888.16" "1" "1" "0")
(command "_insert" "blkuc1" "320,887.79" "1" "1" "180")
(command "_insert" "blkuc1" "320,888.53" "1" "1" "0")
(command "_insert" "blkuc1" "320,888.16" "1" "1" "180")
(command "_insert" "blkuc1" "320,888.9" "1" "1" "0")
(command "_insert" "blkuc1" "320,888.53" "1" "1" "180")
(command "_insert" "blkuc1" "320,889.27" "1" "1" "0")
(command "_insert" "blkuc1" "320,888.9" "1" "1" "180")
(command "_insert" "blkuc1" "320,889.64" "1" "1" "0")
(command "_insert" "blkuc1" "320,889.27" "1" "1" "180")
(command "_insert" "blkuc1" "320,890.01" "1" "1" "0")
(command "_insert" "blkuc1" "320,889.64" "1" "1" "180")
(command "_insert" "blkuc1" "320,890.38" "1" "1" "0")
(command "_insert" "blkuc1" "320,890.01" "1" "1" "180")
(command "_insert" "blkuc1" "320,890.75" "1" "1" "0")
(command "_insert" "blkuc1" "320,890.38" "1" "1" "180")
(command "_insert" "blkuc1" "320,891.12" "1" "1" "0")
(command "_insert" "blkuc1" "320,890.75" "1" "1" "180")
(command "_insert" "blkuc1" "320,891.49" "1" "1" "0")
(command "_insert" "blkuc1" "320,891.12" "1" "1" "180")
(command "_insert" "blkuc1" "320,891.86" "1" "1" "0")
(command "_insert" "blkuc1" "320,891.49" "1" "1" "180")
(command "_insert" "blkuc1" "320,892.23" "1" "1" "0")
(command "_insert" "blkuc1" "320,891.86" "1" "1" "180")
(command "_insert" "blkuc1" "320,892.6" "1" "1" "0")
(command "_insert" "blkuc1" "320,892.23" "1" "1" "180")
(command "_insert" "blkuc1" "320,892.97" "1" "1" "0")
(command "_insert" "blkuc1" "320,892.6" "1" "1" "180")
(command "_insert" "blkuc1" "320,893.34" "1" "1" "0")
(command "_insert" "blkuc1" "320,892.97" "1" "1" "180")
(command "_insert" "blkuc1" "320,893.71" "1" "1" "0")
(command "_insert" "blkuc1" "320,893.34" "1" "1" "180")
(command "_insert" "blkuc1" "320,894.08" "1" "1" "0")
(command "_insert" "blkuc1" "320,893.71" "1" "1" "180")
(command "_insert" "blkuc1" "320,894.45" "1" "1" "0")
(command "_insert" "blkuc1" "320,894.08" "1" "1" "180")
(command "_insert" "blkuc1" "320,894.82" "1" "1" "0")
(command "_insert" "blkuc1" "320,894.45" "1" "1" "180")
(command "_insert" "blkuc1" "320,895.19" "1" "1" "0")
(command "_insert" "blkuc1" "320,894.82" "1" "1" "180")
(command "_insert" "blkuc1" "320,895.56" "1" "1" "0")
(command "_insert" "blkuc1" "320,895.19" "1" "1" "180")
(command "_insert" "blkuc1" "320,895.93" "1" "1" "0")
(command "_insert" "blkuc1" "320,895.56" "1" "1" "180")
(command "_insert" "blkuc1" "320,896.3" "1" "1" "0")
(command "_insert" "blkuc1" "320,895.93" "1" "1" "180")
(command "_insert" "blkuc1" "320,896.67" "1" "1" "0")
(command "_insert" "blkuc1" "320,896.3" "1" "1" "180")
(command "_insert" "blkuc1" "320,897.04" "1" "1" "0")
(command "_insert" "blkuc1" "320,896.67" "1" "1" "180")
(command "_insert" "blkuc1" "320,897.41" "1" "1" "0")
(command "_insert" "blkuc1" "320,897.04" "1" "1" "180")
(command "_insert" "blkuc1" "320,897.78" "1" "1" "0")
(command "_insert" "blkuc1" "320,897.41" "1" "1" "180")
(command "_insert" "blkuc1" "320,898.15" "1" "1" "0")
(command "_insert" "blkuc1" "320,897.78" "1" "1" "180")
(command "_insert" "blkuc1" "320,898.52" "1" "1" "0")
(command "_insert" "blkuc1" "320,898.15" "1" "1" "180")
(command "_insert" "blkuc1" "320,898.89" "1" "1" "0")
(command "_insert" "blkuc1" "320,898.52" "1" "1" "180")
(command "_insert" "blkuc1" "320,899.26" "1" "1" "0")
(command "_insert" "blkuc1" "320,898.89" "1" "1" "180")
(command "_insert" "blkuc1" "320,899.63" "1" "1" "0")
(command "_insert" "blkuc1" "320,899.26" "1" "1" "180")
(command "_insert" "blkuc1" "320,900" "1" "1" "0")
(command "_insert" "blkuc1" "320,899.63" "1" "1" "180")
(command "_insert" "blkuc1" "320,900.37" "1" "1" "0")
(command "_insert" "blkuc1" "320,900" "1" "1" "180")
(command "_insert" "blkuc1" "320,900.74" "1" "1" "0")
(command "_insert" "blkuc1" "320,900.37" "1" "1" "180")
(command "_insert" "blkuc1" "320,901.11" "1" "1" "0")
(command "_insert" "blkuc1" "320,900.74" "1" "1" "180")
(command "_insert" "blkuc1" "320,901.48" "1" "1" "0")
(command "_insert" "blkuc1" "320,901.11" "1" "1" "180")
(command "_insert" "blkuc1" "320,901.85" "1" "1" "0")
(command "_insert" "blkuc1" "320,901.48" "1" "1" "180")
(command "_insert" "blkuc1" "320,902.22" "1" "1" "0")
(command "_insert" "blkuc1" "320,901.85" "1" "1" "180")
(command "_insert" "blkuc1" "320,902.59" "1" "1" "0")
(command "_insert" "blkuc1" "320,902.22" "1" "1" "180")
(command "_insert" "blkuc1" "320,902.96" "1" "1" "0")
(command "_insert" "blkuc1" "320,902.59" "1" "1" "180")
(command "_insert" "blkuc1" "320,903.33" "1" "1" "0")
(command "_insert" "blkuc1" "320,902.96" "1" "1" "180")
(command "_insert" "blkuc1" "320,903.7" "1" "1" "0")
(command "_insert" "blkuc1" "320,903.33" "1" "1" "180")
(command "_insert" "blkuc1" "320,904.07" "1" "1" "0")
(command "_insert" "blkuc1" "320,903.7" "1" "1" "180")
(command "_insert" "blkuc1" "320,904.44" "1" "1" "0")
(command "_insert" "blkuc1" "320,904.07" "1" "1" "180")
(command "_insert" "blkuc1" "320,904.81" "1" "1" "0")
(command "_insert" "blkuc1" "320,904.44" "1" "1" "180")
(command "_insert" "blkuc1" "320,905.18" "1" "1" "0")
(command "_insert" "blkuc1" "320,904.81" "1" "1" "180")
(command "_insert" "blkuc1" "320,905.55" "1" "1" "0")
(command "_insert" "blkuc1" "320,905.18" "1" "1" "180")
(command "_insert" "blkuc1" "320,905.92" "1" "1" "0")
(command "_insert" "blkuc1" "320,905.55" "1" "1" "180")
(command "_insert" "blkuc1" "320,906.29" "1" "1" "0")
(command "_insert" "blkuc1" "320,905.92" "1" "1" "180")
(command "_insert" "blkuc1" "320,906.66" "1" "1" "0")
(command "_insert" "blkuc1" "320,906.29" "1" "1" "180")
(command "_insert" "blkuc1" "320,907.03" "1" "1" "0")
(command "_insert" "blkuc1" "320,906.66" "1" "1" "180")
(command "_insert" "blkuc1" "320,907.4" "1" "1" "0")
(command "_insert" "blkuc1" "320,907.03" "1" "1" "180")
(command "_insert" "blkuc1" "320,907.77" "1" "1" "0")
(command "_insert" "blkuc1" "320,907.4" "1" "1" "180")
(command "_insert" "blkuc1" "320,908.14" "1" "1" "0")
(command "_insert" "blkuc1" "320,907.77" "1" "1" "180")
(command "_insert" "blkuc1" "320,908.51" "1" "1" "0")
(command "_insert" "blkuc1" "320,908.14" "1" "1" "180")
(command "_insert" "blkuc1" "320,908.88" "1" "1" "0")
(command "_insert" "blkuc1" "320,908.51" "1" "1" "180")
(command "_insert" "blkuc1" "320,909.25" "1" "1" "0")
(command "_insert" "blkuc1" "320,908.88" "1" "1" "180")
(command "_insert" "blkuc1" "320,909.62" "1" "1" "0")
(command "_insert" "blkuc1" "320,909.25" "1" "1" "180")
(command "_insert" "blkuc1" "320,909.99" "1" "1" "0")
(command "_insert" "blkuc1" "320,909.62" "1" "1" "180")
(command "_insert" "blkuc1" "320,910.36" "1" "1" "0")
(command "_insert" "blkuc1" "320,909.99" "1" "1" "180")
(command "_insert" "blkuc1" "320,910.73" "1" "1" "0")
(command "_insert" "blkuc1" "320,910.36" "1" "1" "180")
(command "_insert" "blkuc1" "320,911.1" "1" "1" "0")
(command "_insert" "blkuc1" "320,910.73" "1" "1" "180")
(command "_insert" "blkuc1" "320,911.47" "1" "1" "0")
(command "_insert" "blkuc1" "320,911.1" "1" "1" "180")
(command "_insert" "blkuc1" "320,911.84" "1" "1" "0")
(command "_insert" "blkuc1" "320,911.47" "1" "1" "180")
(command "_insert" "blkuc1" "320,912.21" "1" "1" "0")
(command "_insert" "blkuc1" "320,911.84" "1" "1" "180")
(command "_insert" "blkuc1" "320,912.58" "1" "1" "0")
(command "_insert" "blkuc1" "320,912.21" "1" "1" "180")
(command "_insert" "blkuc1" "320,912.95" "1" "1" "0")
(command "_insert" "blkuc1" "320,912.58" "1" "1" "180")
(command "_insert" "blkuc1" "320,913.32" "1" "1" "0")
(command "_insert" "blkuc1" "320,912.95" "1" "1" "180")
(command "_insert" "blkuc1" "320,913.69" "1" "1" "0")
(command "_insert" "blkuc1" "320,913.32" "1" "1" "180")
(command "_insert" "blkuc1" "320,914.06" "1" "1" "0")
(command "_insert" "blkuc1" "320,913.69" "1" "1" "180")
(command "_insert" "blkuc1" "320,914.43" "1" "1" "0")
(command "_insert" "blkuc1" "320,914.06" "1" "1" "180")
(command "_insert" "blkuc1" "320,914.8" "1" "1" "0")
(command "_insert" "blkuc1" "320,914.43" "1" "1" "180")
(command "_insert" "blkuc1" "320,915.17" "1" "1" "0")
(command "_insert" "blkuc1" "320,914.8" "1" "1" "180")
(command "_insert" "blkuc1" "320,915.54" "1" "1" "0")
(command "_insert" "blkuc1" "320,915.17" "1" "1" "180")
(command "_insert" "blkuc1" "320,915.91" "1" "1" "0")
(command "_insert" "blkuc1" "320,915.54" "1" "1" "180")
(command "_insert" "blkuc1" "320,916.28" "1" "1" "0")
(command "_insert" "blkuc1" "320,915.91" "1" "1" "180")
(command "_insert" "blkuc1" "320,916.65" "1" "1" "0")
(command "_insert" "blkuc1" "320,916.28" "1" "1" "180")
(command "_insert" "blkuc1" "320,917.02" "1" "1" "0")
(command "_insert" "blkuc1" "320,916.65" "1" "1" "180")
(command "_insert" "blkuc1" "320,917.39" "1" "1" "0")
(command "_insert" "blkuc1" "320,917.02" "1" "1" "180")
(command "_insert" "blkuc1" "320,917.76" "1" "1" "0")
(command "_insert" "blkuc1" "320,917.39" "1" "1" "180")
(command "_insert" "blkuc1" "320,918.13" "1" "1" "0")
(command "_insert" "blkuc1" "320,917.76" "1" "1" "180")
(command "_insert" "blkuc1" "320,918.5" "1" "1" "0")
(command "_insert" "blkuc1" "320,918.13" "1" "1" "180")
(command "_insert" "blkuc1" "320,918.87" "1" "1" "0")
(command "_insert" "blkuc1" "320,918.5" "1" "1" "180")
(command "_insert" "blkuc1" "320,919.24" "1" "1" "0")
(command "_insert" "blkuc1" "320,918.87" "1" "1" "180")
(command "_insert" "blkuc1" "320,919.61" "1" "1" "0")
(command "_insert" "blkuc1" "320,919.24" "1" "1" "180")
(command "_insert" "blkuc1" "320,919.98" "1" "1" "0")
(command "_insert" "blkuc1" "320,919.61" "1" "1" "180")
(command "_insert" "blkuc1" "320,920.35" "1" "1" "0")
(command "_insert" "blkuc1" "320,919.98" "1" "1" "180")
(command "_insert" "blkuc1" "320,920.72" "1" "1" "0")
(command "_insert" "blkuc1" "320,920.35" "1" "1" "180")
(command "_insert" "blkuc1" "320,921.09" "1" "1" "0")
(command "_insert" "blkuc1" "320,920.72" "1" "1" "180")
(command "_insert" "blkuc1" "320,921.46" "1" "1" "0")
(command "_insert" "blkuc1" "320,921.09" "1" "1" "180")
(command "_insert" "blkuc1" "320,921.83" "1" "1" "0")
(command "_insert" "blkuc1" "320,921.46" "1" "1" "180")
(command "_insert" "blkuc1" "320,922.2" "1" "1" "0")
(command "_insert" "blkuc1" "320,921.83" "1" "1" "180")
(command "_insert" "blkuc1" "320,922.57" "1" "1" "0")
(command "_insert" "blkuc1" "320,922.2" "1" "1" "180")
(command "_insert" "blkuc1" "320,922.94" "1" "1" "0")
(command "_insert" "blkuc1" "320,922.57" "1" "1" "180")
(command "_insert" "blkuc1" "320,923.31" "1" "1" "0")
(command "_insert" "blkuc1" "320,922.94" "1" "1" "180")
(command "_insert" "blkuc1" "320,923.68" "1" "1" "0")
(command "_insert" "blkuc1" "320,923.31" "1" "1" "180")
(command "_insert" "blkuc1" "320,924.05" "1" "1" "0")
(command "_insert" "blkuc1" "320,923.68" "1" "1" "180")
(command "_insert" "blkuc1" "320,924.42" "1" "1" "0")
(command "_insert" "blkuc1" "320,924.05" "1" "1" "180")
(command "_insert" "blkuc1" "320,924.79" "1" "1" "0")
(command "_insert" "blkuc1" "320,924.42" "1" "1" "180")
(command "_insert" "blkuc1" "320,925.16" "1" "1" "0")
(command "_insert" "blkuc1" "320,924.79" "1" "1" "180")
(command "_insert" "blkuc1" "320,925.53" "1" "1" "0")
(command "_insert" "blkuc1" "320,925.16" "1" "1" "180")
(command "_insert" "blkuc1" "320,925.9" "1" "1" "0")
(command "_insert" "blkuc1" "320,925.53" "1" "1" "180")
(command "_insert" "blkuc1" "320,926.27" "1" "1" "0")
(command "_insert" "blkuc1" "320,925.9" "1" "1" "180")
(command "_insert" "blkuc1" "320,926.64" "1" "1" "0")
(command "_insert" "blkuc1" "320,926.27" "1" "1" "180")
(command "_insert" "blkuc1" "320,927.01" "1" "1" "0")
(command "_insert" "blkuc1" "320,926.64" "1" "1" "180")
(command "_insert" "blkuc1" "320,927.38" "1" "1" "0")
(command "_insert" "blkuc1" "320,927.01" "1" "1" "180")
(command "_insert" "blkuc1" "320,927.75" "1" "1" "0")
(command "_insert" "blkuc1" "320,927.38" "1" "1" "180")
(command "_layer" "set" "phccover" "")
(command "_rectangle" "318.934,933.3" "321.066,866.7")
(command "_layer" "set" "nitride" "")
(setq phc1 currobj)
(command "_layer" "set" "cover" "")
(command "_rectangle" "318.934,836.7" "321.066,963.3")
(command "_layer" "set" "nitride" "")
(command "_layer" "set" "text" "")
(command "_circle" "317.984,846.7" "0.075")
(command "_circle" "317.609,846.7" "0.15")
(command "_circle" "317.234,846.7" "0.075")
(command "_circle" "316.859,846.7" "0.15")
(command "_circle" "317.984,848.7" "0.075")
(command "_circle" "317.609,848.7" "0.075")
(command "_circle" "317.234,848.7" "0.15")
(command "_circle" "316.859,848.7" "0.15")
(command "_circle" "317.984,850.7" "0.075")
(command "_circle" "317.609,850.7" "0.15")
(command "_circle" "317.234,850.7" "0.15")
(command "_circle" "316.859,850.7" "0.15")
(command "_circle" "317.984,852.7" "0.075")
(command "_circle" "317.609,852.7" "0.075")
(command "_circle" "317.234,852.7" "0.075")
(command "_circle" "316.859,852.7" "0.075")
(command "_circle" "316.484,852.7" "0.15")
(command "_circle" "317.984,854.7" "0.075")
(command "_circle" "317.609,854.7" "0.15")
(command "_circle" "317.234,854.7" "0.075")
(command "_circle" "316.859,854.7" "0.075")
(command "_circle" "316.484,854.7" "0.15")
(command "_circle" "317.984,856.7" "0.075")
(command "_circle" "317.609,856.7" "0.075")
(command "_circle" "317.234,856.7" "0.15")
(command "_circle" "316.859,856.7" "0.075")
(command "_circle" "316.484,856.7" "0.15")
(command "_circle" "317.984,858.7" "0.075")
(command "_circle" "317.609,858.7" "0.15")
(command "_circle" "317.234,858.7" "0.15")
(command "_circle" "316.859,858.7" "0.075")
(command "_circle" "316.484,858.7" "0.15")
(command "_circle" "317.984,860.7" "0.075")
(command "_circle" "317.609,860.7" "0.075")
(command "_circle" "317.234,860.7" "0.075")
(command "_circle" "316.859,860.7" "0.15")
(command "_circle" "316.484,860.7" "0.15")
(command "_circle" "317.984,862.7" "0.075")
(command "_circle" "317.609,862.7" "0.15")
(command "_circle" "317.234,862.7" "0.075")
(command "_circle" "316.859,862.7" "0.15")
(command "_circle" "316.484,862.7" "0.15")
(command "_circle" "317.984,864.7" "0.075")
(command "_circle" "317.609,864.7" "0.075")
(command "_circle" "317.234,864.7" "0.15")
(command "_circle" "316.859,864.7" "0.15")
(command "_circle" "316.484,864.7" "0.15")
(command "_circle" "317.984,866.7" "0.075")
(command "_circle" "317.609,866.7" "0.15")
(command "_circle" "317.234,866.7" "0.15")
(command "_circle" "316.859,866.7" "0.15")
(command "_circle" "316.484,866.7" "0.15")
(command "_circle" "317.984,868.7" "0.075")
(command "_circle" "317.609,868.7" "0.075")
(command "_circle" "317.234,868.7" "0.075")
(command "_circle" "316.859,868.7" "0.075")
(command "_circle" "316.484,868.7" "0.075")
(command "_circle" "316.109,868.7" "0.15")
(command "_circle" "317.984,870.7" "0.075")
(command "_circle" "317.609,870.7" "0.15")
(command "_circle" "317.234,870.7" "0.075")
(command "_circle" "316.859,870.7" "0.075")
(command "_circle" "316.484,870.7" "0.075")
(command "_circle" "316.109,870.7" "0.15")
(command "_circle" "317.984,872.7" "0.075")
(command "_circle" "317.609,872.7" "0.075")
(command "_circle" "317.234,872.7" "0.15")
(command "_circle" "316.859,872.7" "0.075")
(command "_circle" "316.484,872.7" "0.075")
(command "_circle" "316.109,872.7" "0.15")
(command "_circle" "317.984,874.7" "0.075")
(command "_circle" "317.609,874.7" "0.15")
(command "_circle" "317.234,874.7" "0.15")
(command "_circle" "316.859,874.7" "0.075")
(command "_circle" "316.484,874.7" "0.075")
(command "_circle" "316.109,874.7" "0.15")
(command "_circle" "317.984,876.7" "0.075")
(command "_circle" "317.609,876.7" "0.075")
(command "_circle" "317.234,876.7" "0.075")
(command "_circle" "316.859,876.7" "0.15")
(command "_circle" "316.484,876.7" "0.075")
(command "_circle" "316.109,876.7" "0.15")
(command "_circle" "317.984,878.7" "0.075")
(command "_circle" "317.609,878.7" "0.15")
(command "_circle" "317.234,878.7" "0.075")
(command "_circle" "316.859,878.7" "0.15")
(command "_circle" "316.484,878.7" "0.075")
(command "_circle" "316.109,878.7" "0.15")
(command "_circle" "317.984,880.7" "0.075")
(command "_circle" "317.609,880.7" "0.075")
(command "_circle" "317.234,880.7" "0.15")
(command "_circle" "316.859,880.7" "0.15")
(command "_circle" "316.484,880.7" "0.075")
(command "_circle" "316.109,880.7" "0.15")
(command "_circle" "317.984,882.7" "0.075")
(command "_circle" "317.609,882.7" "0.15")
(command "_circle" "317.234,882.7" "0.15")
(command "_circle" "316.859,882.7" "0.15")
(command "_circle" "316.484,882.7" "0.075")
(command "_circle" "316.109,882.7" "0.15")
(command "_circle" "317.984,884.7" "0.075")
(command "_circle" "317.609,884.7" "0.075")
(command "_circle" "317.234,884.7" "0.075")
(command "_circle" "316.859,884.7" "0.075")
(command "_circle" "316.484,884.7" "0.15")
(command "_circle" "316.109,884.7" "0.15")
(command "_circle" "317.984,886.7" "0.075")
(command "_circle" "317.609,886.7" "0.15")
(command "_circle" "317.234,886.7" "0.075")
(command "_circle" "316.859,886.7" "0.075")
(command "_circle" "316.484,886.7" "0.15")
(command "_circle" "316.109,886.7" "0.15")
(command "_circle" "317.984,888.7" "0.075")
(command "_circle" "317.609,888.7" "0.075")
(command "_circle" "317.234,888.7" "0.15")
(command "_circle" "316.859,888.7" "0.075")
(command "_circle" "316.484,888.7" "0.15")
(command "_circle" "316.109,888.7" "0.15")
(command "_circle" "317.984,890.7" "0.075")
(command "_circle" "317.609,890.7" "0.15")
(command "_circle" "317.234,890.7" "0.15")
(command "_circle" "316.859,890.7" "0.075")
(command "_circle" "316.484,890.7" "0.15")
(command "_circle" "316.109,890.7" "0.15")
(command "_circle" "317.984,892.7" "0.075")
(command "_circle" "317.609,892.7" "0.075")
(command "_circle" "317.234,892.7" "0.075")
(command "_circle" "316.859,892.7" "0.15")
(command "_circle" "316.484,892.7" "0.15")
(command "_circle" "316.109,892.7" "0.15")
(command "_circle" "317.984,894.7" "0.075")
(command "_circle" "317.609,894.7" "0.15")
(command "_circle" "317.234,894.7" "0.075")
(command "_circle" "316.859,894.7" "0.15")
(command "_circle" "316.484,894.7" "0.15")
(command "_circle" "316.109,894.7" "0.15")
(command "_circle" "317.984,896.7" "0.075")
(command "_circle" "317.609,896.7" "0.075")
(command "_circle" "317.234,896.7" "0.15")
(command "_circle" "316.859,896.7" "0.15")
(command "_circle" "316.484,896.7" "0.15")
(command "_circle" "316.109,896.7" "0.15")
(command "_circle" "317.984,898.7" "0.075")
(command "_circle" "317.609,898.7" "0.15")
(command "_circle" "317.234,898.7" "0.15")
(command "_circle" "316.859,898.7" "0.15")
(command "_circle" "316.484,898.7" "0.15")
(command "_circle" "316.109,898.7" "0.15")
(command "_circle" "317.984,900.7" "0.075")
(command "_circle" "317.609,900.7" "0.075")
(command "_circle" "317.234,900.7" "0.075")
(command "_circle" "316.859,900.7" "0.075")
(command "_circle" "316.484,900.7" "0.075")
(command "_circle" "316.109,900.7" "0.075")
(command "_circle" "315.734,900.7" "0.15")
(command "_circle" "317.984,902.7" "0.075")
(command "_circle" "317.609,902.7" "0.15")
(command "_circle" "317.234,902.7" "0.075")
(command "_circle" "316.859,902.7" "0.075")
(command "_circle" "316.484,902.7" "0.075")
(command "_circle" "316.109,902.7" "0.075")
(command "_circle" "315.734,902.7" "0.15")
(command "_circle" "317.984,904.7" "0.075")
(command "_circle" "317.609,904.7" "0.075")
(command "_circle" "317.234,904.7" "0.15")
(command "_circle" "316.859,904.7" "0.075")
(command "_circle" "316.484,904.7" "0.075")
(command "_circle" "316.109,904.7" "0.075")
(command "_circle" "315.734,904.7" "0.15")
(command "_circle" "317.984,906.7" "0.075")
(command "_circle" "317.609,906.7" "0.15")
(command "_circle" "317.234,906.7" "0.15")
(command "_circle" "316.859,906.7" "0.075")
(command "_circle" "316.484,906.7" "0.075")
(command "_circle" "316.109,906.7" "0.075")
(command "_circle" "315.734,906.7" "0.15")
(command "_circle" "317.984,908.7" "0.075")
(command "_circle" "317.609,908.7" "0.075")
(command "_circle" "317.234,908.7" "0.075")
(command "_circle" "316.859,908.7" "0.15")
(command "_circle" "316.484,908.7" "0.075")
(command "_circle" "316.109,908.7" "0.075")
(command "_circle" "315.734,908.7" "0.15")
(command "_circle" "317.984,910.7" "0.075")
(command "_circle" "317.609,910.7" "0.15")
(command "_circle" "317.234,910.7" "0.075")
(command "_circle" "316.859,910.7" "0.15")
(command "_circle" "316.484,910.7" "0.075")
(command "_circle" "316.109,910.7" "0.075")
(command "_circle" "315.734,910.7" "0.15")
(command "_circle" "317.984,912.7" "0.075")
(command "_circle" "317.609,912.7" "0.075")
(command "_circle" "317.234,912.7" "0.15")
(command "_circle" "316.859,912.7" "0.15")
(command "_circle" "316.484,912.7" "0.075")
(command "_circle" "316.109,912.7" "0.075")
(command "_circle" "315.734,912.7" "0.15")
(command "_circle" "317.984,914.7" "0.075")
(command "_circle" "317.609,914.7" "0.15")
(command "_circle" "317.234,914.7" "0.15")
(command "_circle" "316.859,914.7" "0.15")
(command "_circle" "316.484,914.7" "0.075")
(command "_circle" "316.109,914.7" "0.075")
(command "_circle" "315.734,914.7" "0.15")
(command "_circle" "317.984,916.7" "0.075")
(command "_circle" "317.609,916.7" "0.075")
(command "_circle" "317.234,916.7" "0.075")
(command "_circle" "316.859,916.7" "0.075")
(command "_circle" "316.484,916.7" "0.15")
(command "_circle" "316.109,916.7" "0.075")
(command "_circle" "315.734,916.7" "0.15")
(command "_circle" "317.984,918.7" "0.075")
(command "_circle" "317.609,918.7" "0.15")
(command "_circle" "317.234,918.7" "0.075")
(command "_circle" "316.859,918.7" "0.075")
(command "_circle" "316.484,918.7" "0.15")
(command "_circle" "316.109,918.7" "0.075")
(command "_circle" "315.734,918.7" "0.15")
(command "_circle" "317.984,920.7" "0.075")
(command "_circle" "317.609,920.7" "0.075")
(command "_circle" "317.234,920.7" "0.15")
(command "_circle" "316.859,920.7" "0.075")
(command "_circle" "316.484,920.7" "0.15")
(command "_circle" "316.109,920.7" "0.075")
(command "_circle" "315.734,920.7" "0.15")
(command "_circle" "317.984,922.7" "0.075")
(command "_circle" "317.609,922.7" "0.15")
(command "_circle" "317.234,922.7" "0.15")
(command "_circle" "316.859,922.7" "0.075")
(command "_circle" "316.484,922.7" "0.15")
(command "_circle" "316.109,922.7" "0.075")
(command "_circle" "315.734,922.7" "0.15")
(command "_circle" "317.984,924.7" "0.075")
(command "_circle" "317.609,924.7" "0.075")
(command "_circle" "317.234,924.7" "0.075")
(command "_circle" "316.859,924.7" "0.15")
(command "_circle" "316.484,924.7" "0.15")
(command "_circle" "316.109,924.7" "0.075")
(command "_circle" "315.734,924.7" "0.15")
(command "_circle" "317.984,926.7" "0.075")
(command "_circle" "317.609,926.7" "0.15")
(command "_circle" "317.234,926.7" "0.075")
(command "_circle" "316.859,926.7" "0.15")
(command "_circle" "316.484,926.7" "0.15")
(command "_circle" "316.109,926.7" "0.075")
(command "_circle" "315.734,926.7" "0.15")
(command "_circle" "317.984,928.7" "0.075")
(command "_circle" "317.609,928.7" "0.075")
(command "_circle" "317.234,928.7" "0.15")
(command "_circle" "316.859,928.7" "0.15")
(command "_circle" "316.484,928.7" "0.15")
(command "_circle" "316.109,928.7" "0.075")
(command "_circle" "315.734,928.7" "0.15")
(command "_circle" "317.984,930.7" "0.075")
(command "_circle" "317.609,930.7" "0.15")
(command "_circle" "317.234,930.7" "0.15")
(command "_circle" "316.859,930.7" "0.15")
(command "_circle" "316.484,930.7" "0.15")
(command "_circle" "316.109,930.7" "0.075")
(command "_circle" "315.734,930.7" "0.15")
(command "_circle" "317.984,932.7" "0.075")
(command "_circle" "317.609,932.7" "0.075")
(command "_circle" "317.234,932.7" "0.075")
(command "_circle" "316.859,932.7" "0.075")
(command "_circle" "316.484,932.7" "0.075")
(command "_circle" "316.109,932.7" "0.15")
(command "_circle" "315.734,932.7" "0.15")
(command "_circle" "317.984,934.7" "0.075")
(command "_circle" "317.609,934.7" "0.15")
(command "_circle" "317.234,934.7" "0.075")
(command "_circle" "316.859,934.7" "0.075")
(command "_circle" "316.484,934.7" "0.075")
(command "_circle" "316.109,934.7" "0.15")
(command "_circle" "315.734,934.7" "0.15")
(command "_circle" "317.984,936.7" "0.075")
(command "_circle" "317.609,936.7" "0.075")
(command "_circle" "317.234,936.7" "0.15")
(command "_circle" "316.859,936.7" "0.075")
(command "_circle" "316.484,936.7" "0.075")
(command "_circle" "316.109,936.7" "0.15")
(command "_circle" "315.734,936.7" "0.15")
(command "_circle" "317.984,938.7" "0.075")
(command "_circle" "317.609,938.7" "0.15")
(command "_circle" "317.234,938.7" "0.15")
(command "_circle" "316.859,938.7" "0.075")
(command "_circle" "316.484,938.7" "0.075")
(command "_circle" "316.109,938.7" "0.15")
(command "_circle" "315.734,938.7" "0.15")
(command "_circle" "317.984,940.7" "0.075")
(command "_circle" "317.609,940.7" "0.075")
(command "_circle" "317.234,940.7" "0.075")
(command "_circle" "316.859,940.7" "0.15")
(command "_circle" "316.484,940.7" "0.075")
(command "_circle" "316.109,940.7" "0.15")
(command "_circle" "315.734,940.7" "0.15")
(command "_circle" "317.984,942.7" "0.075")
(command "_circle" "317.609,942.7" "0.15")
(command "_circle" "317.234,942.7" "0.075")
(command "_circle" "316.859,942.7" "0.15")
(command "_circle" "316.484,942.7" "0.075")
(command "_circle" "316.109,942.7" "0.15")
(command "_circle" "315.734,942.7" "0.15")
(command "_circle" "317.984,944.7" "0.075")
(command "_circle" "317.609,944.7" "0.075")
(command "_circle" "317.234,944.7" "0.15")
(command "_circle" "316.859,944.7" "0.15")
(command "_circle" "316.484,944.7" "0.075")
(command "_circle" "316.109,944.7" "0.15")
(command "_circle" "315.734,944.7" "0.15")
(command "_circle" "317.984,946.7" "0.075")
(command "_circle" "317.609,946.7" "0.15")
(command "_circle" "317.234,946.7" "0.15")
(command "_circle" "316.859,946.7" "0.15")
(command "_circle" "316.484,946.7" "0.075")
(command "_circle" "316.109,946.7" "0.15")
(command "_circle" "315.734,946.7" "0.15")
(command "_circle" "317.984,948.7" "0.075")
(command "_circle" "317.609,948.7" "0.075")
(command "_circle" "317.234,948.7" "0.075")
(command "_circle" "316.859,948.7" "0.075")
(command "_circle" "316.484,948.7" "0.15")
(command "_circle" "316.109,948.7" "0.15")
(command "_circle" "315.734,948.7" "0.15")
(command "_circle" "317.984,950.7" "0.075")
(command "_circle" "317.609,950.7" "0.15")
(command "_circle" "317.234,950.7" "0.075")
(command "_circle" "316.859,950.7" "0.075")
(command "_circle" "316.484,950.7" "0.15")
(command "_circle" "316.109,950.7" "0.15")
(command "_circle" "315.734,950.7" "0.15")
(command "_circle" "317.984,952.7" "0.075")
(command "_circle" "317.609,952.7" "0.075")
(command "_circle" "317.234,952.7" "0.15")
(command "_circle" "316.859,952.7" "0.075")
(command "_circle" "316.484,952.7" "0.15")
(command "_circle" "316.109,952.7" "0.15")
(command "_circle" "315.734,952.7" "0.15")
(command "_circle" "317.984,954.7" "0.075")
(command "_circle" "317.609,954.7" "0.15")
(command "_circle" "317.234,954.7" "0.15")
(command "_circle" "316.859,954.7" "0.075")
(command "_circle" "316.484,954.7" "0.15")
(command "_circle" "316.109,954.7" "0.15")
(command "_circle" "315.734,954.7" "0.15")
(command "_circle" "317.984,956.7" "0.075")
(command "_circle" "317.609,956.7" "0.075")
(command "_circle" "317.234,956.7" "0.075")
(command "_circle" "316.859,956.7" "0.15")
(command "_circle" "316.484,956.7" "0.15")
(command "_circle" "316.109,956.7" "0.15")
(command "_circle" "315.734,956.7" "0.15")
(command "_circle" "317.984,958.7" "0.075")
(command "_circle" "317.609,958.7" "0.15")
(command "_circle" "317.234,958.7" "0.075")
(command "_circle" "316.859,958.7" "0.15")
(command "_circle" "316.484,958.7" "0.15")
(command "_circle" "316.109,958.7" "0.15")
(command "_circle" "315.734,958.7" "0.15")
(command "_circle" "317.984,960.7" "0.075")
(command "_circle" "317.609,960.7" "0.075")
(command "_circle" "317.234,960.7" "0.15")
(command "_circle" "316.859,960.7" "0.15")
(command "_circle" "316.484,960.7" "0.15")
(command "_circle" "316.109,960.7" "0.15")
(command "_circle" "315.734,960.7" "0.15")
(command "_circle" "317.984,962.7" "0.075")
(command "_circle" "317.609,962.7" "0.15")
(command "_circle" "317.234,962.7" "0.15")
(command "_circle" "316.859,962.7" "0.15")
(command "_circle" "316.484,962.7" "0.15")
(command "_circle" "316.109,962.7" "0.15")
(command "_circle" "315.734,962.7" "0.15")
(command "_layer" "set" "nitride" "")
(command "_layer" "set" "text" "")
(command-s "_text" "306.934,963.3" "2" "-90" "a = 370 nm" )
(sssetfirst nil (ssget "_L"))
(if (not (numberp (vl-string-search "Mac" (getvar "platform")))) (c:txtexp))
(command "_layer" "set" "nitride" "")
(command "_layer" "set" "text" "")
(command-s "_text" "303.934,963.3" "2" "-90" "gap = 270 nm" )
(sssetfirst nil (ssget "_L"))
(if (not (numberp (vl-string-search "Mac" (getvar "platform")))) (c:txtexp))
(command "_layer" "set" "nitride" "")
(command "_layer" "set" "text" "")
(command-s "_text" "300.934,963.3" "2" "-90" "amplitude = 122 nm" )
(sssetfirst nil (ssget "_L"))
(if (not (numberp (vl-string-search "Mac" (getvar "platform")))) (c:txtexp))
(command "_layer" "set" "nitride" "")
(command "_layer" "set" "text" "")
(command-s "_text" "297.934,963.3" "2" "-90" "start width = 280 nm" )
(sssetfirst nil (ssget "_L"))
(if (not (numberp (vl-string-search "Mac" (getvar "platform")))) (c:txtexp))
(command "_layer" "set" "nitride" "")
(command "_layer" "set" "text" "")
(command-s "_text" "294.934,963.3" "2" "-90" "width = 276 nm" )
(sssetfirst nil (ssget "_L"))
(if (not (numberp (vl-string-search "Mac" (getvar "platform")))) (c:txtexp))
(command "_layer" "set" "nitride" "")
(command "_layer" "set" "text" "")
(command-s "_text" "291.934,963.3" "2" "-90" "taper: 15" )
(sssetfirst nil (ssget "_L"))
(if (not (numberp (vl-string-search "Mac" (getvar "platform")))) (c:txtexp))
(command "_layer" "set" "nitride" "")
(command "_layer" "set" "text" "")
(command-s "_text" "288.934,963.3" "2" "-90" "nominal: 150" )
(sssetfirst nil (ssget "_L"))
(if (not (numberp (vl-string-search "Mac" (getvar "platform")))) (c:txtexp))
(command "_layer" "set" "nitride" "")
(command "_layer" "set" "indicators" "")
(setq coords (list 
(list 240.415 940) 
(list 240.415 920) 
(list 220.415 900) 
(list 240.415 880) 
(list 240.415 860) 
(list 240.415 900) 
(list 240.415 887.0711) 
(list 227.4861 900) 
(list 240.415 912.9289) 
(list 240.415 900)))
(apply 'command (append '("pline") coords '("c")))
(command "._fillet" "radius" "1" "._fillet" "P" (entlast))
(setq coords (list 
(list 399.585 940) 
(list 399.585 920) 
(list 419.585 900) 
(list 399.585 880) 
(list 399.585 860) 
(list 399.585 900) 
(list 399.585 887.0711) 
(list 412.5139 900) 
(list 399.585 912.9289) 
(list 399.585 900)))
(apply 'command (append '("pline") coords '("c")))
(command "._fillet" "radius" "1" "._fillet" "P" (entlast))
(command "_layer" "set" "holes" "")
(command "_circle" "238.0629,914.1124" "0.5")
(command "_circle" "235.7109,911.7603" "0.5")
(command "_circle" "233.3588,909.4083" "0.5")
(command "_circle" "231.0067,907.0562" "0.5")
(command "_circle" "228.6547,904.7041" "0.5")
(command "_circle" "226.3026,902.3521" "0.5")
(command "_circle" "223.9505,900" "0.5")
(command "_circle" "226.3026,897.6479" "0.5")
(command "_circle" "228.6547,895.2959" "0.5")
(command "_circle" "231.0067,892.9438" "0.5")
(command "_circle" "233.3588,890.5917" "0.5")
(command "_circle" "235.7109,888.2397" "0.5")
(command "_circle" "238.0629,885.8876" "0.5")
(command "_circle" "401.9371,914.1124" "0.5")
(command "_circle" "404.2891,911.7603" "0.5")
(command "_circle" "406.6412,909.4083" "0.5")
(command "_circle" "408.9933,907.0562" "0.5")
(command "_circle" "411.3453,904.7041" "0.5")
(command "_circle" "413.6974,902.3521" "0.5")
(command "_circle" "416.0495,900" "0.5")
(command "_circle" "413.6974,897.6479" "0.5")
(command "_circle" "411.3453,895.2959" "0.5")
(command "_circle" "408.9933,892.9438" "0.5")
(command "_circle" "406.6412,890.5917" "0.5")
(command "_circle" "404.2891,888.2397" "0.5")
(command "_circle" "401.9371,885.8876" "0.5")
(command "_layer" "set" "nitride" "")
(command "_block" "blkcoupler1" "320,900" coupler1 "")
(command "_insert" "blkcoupler1" "320,900" "1" "1" "0")
(command "_insert" "blkcoupler1" "320,900" "1" "1" "180")
(command "_block" "blksinglenanobeam1" "320,900" singlenanobeam1 "")
(command "_insert" "blksinglenanobeam1" "320,900" "1" "1" "0")
(command "_insert" "blksinglenanobeam1" "320,900" "1" "1" "180")
(command "_block" "blkanglednodearray1" "320,900" anglednodearray1 "")
(command "_insert" "blkanglednodearray1" "320,900" "1" "1" "0")
(command "_insert" "blkanglednodearray1" "320,900" "1" "1" "180")
(command "_block" "blkcooledsinglenanobeam1" "320,900" cooledsinglenanobeam1 "")
(command "_insert" "blkcooledsinglenanobeam1" "320,900" "1" "1" "0")
(command "_insert" "blkcooledsinglenanobeam1" "320,900" "1" "1" "180")
(command "_block" "blkyjunction1" "320,900" yjunction1 "")
(command "_insert" "blkyjunction1" "320,900" "1" "1" "0")
(command "_insert" "blkyjunction1" "320,900" "1" "1" "180")
; DRAWING BULGING VEE GROOVE
(command "_layer" "set" "vgroove" "")
(setq coords (list 
(list 245.415 -605) 
(list 245.415 0) 
(list 245.415 0) 
(list 245.415 1800) 
(list 245.415 1800) 
(list 245.415 2405) 
(list 394.585 2405) 
(list 394.585 1800) 
(list 394.585 1800) 
(list 394.585 0) 
(list 394.585 0) 
(list 394.585 -605)))
(apply 'command (append '("pline") coords '("c")))
(command "._fillet" "radius" "0" "._fillet" "P" (entlast))
(command "_layer" "set" "window" "")
(command "_rectangle" "245.415,-1935" "394.585,-600")
(command "_rectangle" "245.415,2400" "394.585,5300")
(command "_layer" "set" "grid" "")
(command "_rectangle" "246.415,-1934" "269.9433,-1909.2133")
(command "_array" "last" "" "R" "75" "3" "25.7867" "24.5283")
(command "_rectangle" "321,-1934" "344.5283,-1909.2133")
(command "_array" "last" "" "R" "75" "3" "25.7867" "24.5283")
(command "_rectangle" "246.415,1" "269.9433,25.7")
(command "_array" "last" "" "R" "70" "3" "25.7" "24.5283")
(command "_rectangle" "321,1" "344.5283,25.7")
(command "_array" "last" "" "R" "70" "3" "25.7" "24.5283")
(command "_rectangle" "246.415,1801" "269.9433,1825.9185")
(command "_array" "last" "" "R" "135" "3" "25.9185" "24.5283")
(command "_rectangle" "321,1801" "344.5283,1825.9185")
(command "_array" "last" "" "R" "135" "3" "25.9185" "24.5283")
(command "_layer" "set" "vgrooveFDA" "")
(command "_rectangle" "394.585,-2233" "245.415,-1933")
(command "_layer" "set" "nitride" "")
(command "_layer" "set" "holes" "")
(command "_circle" "397.085,331.5" "0.5")
(command "_array" "last" "" "R" "379" "1" "3" "2.5")
(command "_circle" "242.915,331.5" "0.5")
(command "_array" "last" "" "R" "379" "1" "3" "-2.5")
(command "_layer" "set" "nitride" "")
(command "_layer" "set" "window" "")
(command "_layer" "set" "window" "")
(command "_rectangle" "240.415,0" "-986.225,1800")
(command "._fillet" "radius" "20" "._fillet" "P" (entlast))
(command "_layer" "set" "grid" "")
(command "_rectangle" "-985.225,1" "-960.6908,25.7")
(command "_array" "last" "" "R" "70" "48" "25.7" "25.5342")
(command "_layer" "set" "window" "")
(command "_rectangle" "399.585,0" "560.415,1800")
(command "._fillet" "radius" "20" "._fillet" "P" (entlast))
(command "_layer" "set" "grid" "")
(command "_rectangle" "400.585,1" "422.4179,25.7")
(command "_array" "last" "" "R" "70" "7" "25.7" "22.8329")
(command "_layer" "set" "nitride" "")
; DRAWING REGION LAYER
(command "_layer" "set" "regionLayer1" "")
(command "_rectangle" "240,-460" "400,2260")
(command "_layer" "set" "nitride" "")
(setq coupler1 nil)
(setq singlenanobeam1 nil)
(setq anglednodearray1 nil)
(setq cooledsinglenanobeam1 nil)
(setq yjunction1 nil)
; DEVICE #2
(command "_layer" "set" "window" "")
(command "_circle" "552.915,-415" "5")
(command "_circle" "552.915,-402.5" "5")
(command "_layer" "set" "nitride" "")
(setq currobj nil)
(setq currobj (ssadd))
; DRAWING COUPLER
(setq coords (list 
(list 640.0555 -415) 
(list 640.0555 -413) 
(list 713.585 -413) 
(list 713.585 -413) 
(list 713.9677 -413.0761) 
(list 714.2921 -413.2929) 
(list 714.5089 -413.6173) 
(list 714.585 -414) 
(list 714.585 -411.8) 
(list 714.585 -411.8) 
(list 714.5089 -412.1827) 
(list 714.2921 -412.5071) 
(list 713.9677 -412.7239) 
(list 713.585 -412.8) 
(list 640.0555 -412.8) 
(list 640.0555 -410.8) 
(list 639.9445 -410.8) 
(list 639.9445 -412.8) 
(list 566.415 -412.8) 
(list 566.0323 -412.7239) 
(list 565.7079 -412.5071) 
(list 565.4911 -412.1827) 
(list 565.415 -411.8) 
(list 565.415 -411.8) 
(list 565.415 -414) 
(list 565.4911 -413.6173) 
(list 565.7079 -413.2929) 
(list 566.0323 -413.0761) 
(list 566.415 -413) 
(list 566.415 -413) 
(list 639.9445 -413) 
(list 639.9445 -415)))
(apply 'command (append '("pline") coords '("c")))
(setq currobj (ssadd (entlast) currobj))
(command "._fillet" "radius" "0.3" "._fillet" "P" (entlast))
(command "_layer" "set" "holes" "")
(command "_circle" "640,-412.9" "0.113")
(setq currobj (ssadd (entlast) currobj))
(command "_layer" "set" "nitride" "")
(command "_layer" "set" "text" "")
(command "_circle" "639.2,-415" "0.075")
(command "_circle" "639.2,-414.7" "0.075")
(command "_circle" "639.2,-414.4" "0.075")
(command "_circle" "638.9,-415" "0.075")
(command "_circle" "638.9,-414.7" "0.075")
(command "_circle" "638.9,-414.4" "0.075")
(command "_circle" "638.6,-415" "0.075")
(command "_circle" "638.6,-414.7" "0.075")
(command "_circle" "638.6,-414.4" "0.075")
(command "_layer" "set" "nitride" "")
(command "_layer" "set" "prebias" "")
(command "_rectangle" "565.415,-414" "714.585,-411.8")
(setq currobj (ssadd (entlast) currobj))
(command "_rectangle" "639.9445,-415" "640.0555,-410.8")
(setq currobj (ssadd (entlast) currobj))
(command "_layer" "set" "nitride" "")
(setq coupler2 currobj)
(setq currobj nil)
(setq currobj (ssadd))
; DRAWING SINGLE NANOBEAM
(setq coords (list 
(list 640.0555 -410.8) 
(list 640.0555 -409.1417) 
(list 640.0555 -407.4833) 
(list 640.0555 -405.825) 
(list 640.0555 -404.1667) 
(list 640.0555 -402.5083) 
(list 640.0555 -400.85) 
(list 640.0555 -399.1917) 
(list 640.0555 -397.5333) 
(list 640.0556 -395.875) 
(list 640.0556 -394.2167) 
(list 640.0556 -392.5583) 
(list 640.0556 -390.9) 
(list 640.0557 -389.2417) 
(list 640.0557 -387.5833) 
(list 640.0558 -385.925) 
(list 640.0558 -384.2667) 
(list 640.0559 -382.6083) 
(list 640.0559 -380.95) 
(list 640.056 -379.2917) 
(list 640.0561 -377.6333) 
(list 640.0562 -375.975) 
(list 640.0563 -374.3167) 
(list 640.0564 -372.6583) 
(list 640.0565 -371) 
(list 640.0567 -369.3417) 
(list 640.0568 -367.6833) 
(list 640.057 -366.025) 
(list 640.0571 -364.3667) 
(list 640.0573 -362.7083) 
(list 640.0575 -361.05) 
(list 640.0577 -359.3917) 
(list 640.058 -357.7333) 
(list 640.0582 -356.075) 
(list 640.0584 -354.4167) 
(list 640.0587 -352.7583) 
(list 640.059 -351.1) 
(list 640.0593 -349.4417) 
(list 640.0596 -347.7833) 
(list 640.0599 -346.125) 
(list 640.0603 -344.4667) 
(list 640.0607 -342.8083) 
(list 640.0611 -341.15) 
(list 640.0615 -339.4917) 
(list 640.0619 -337.8333) 
(list 640.0623 -336.175) 
(list 640.0628 -334.5167) 
(list 640.0633 -332.8583) 
(list 640.0638 -331.2) 
(list 640.0643 -329.5417) 
(list 640.0649 -327.8833) 
(list 640.0654 -326.225) 
(list 640.066 -324.5667) 
(list 640.0667 -322.9083) 
(list 640.0673 -321.25) 
(list 640.068 -319.5917) 
(list 640.0687 -317.9333) 
(list 640.0694 -316.275) 
(list 640.0701 -314.6167) 
(list 640.0709 -312.9583) 
(list 640.0717 -311.3) 
(list 640.0725 -309.6417) 
(list 640.0734 -307.9833) 
(list 640.0742 -306.325) 
(list 640.0751 -304.6667) 
(list 640.0761 -303.0083) 
(list 640.077 -301.35) 
(list 640.078 -299.6917) 
(list 640.0791 -298.0333) 
(list 640.0801 -296.375) 
(list 640.0812 -294.7167) 
(list 640.0823 -293.0583) 
(list 640.0835 -291.4) 
(list 640.0847 -289.7417) 
(list 640.0859 -288.0833) 
(list 640.0871 -286.425) 
(list 640.0884 -284.7667) 
(list 640.0897 -283.1083) 
(list 640.0911 -281.45) 
(list 640.0924 -279.7917) 
(list 640.0939 -278.1333) 
(list 640.0953 -276.475) 
(list 640.0968 -274.8167) 
(list 640.0984 -273.1583) 
(list 640.0999 -271.5) 
(list 640.1015 -269.8417) 
(list 640.1032 -268.1833) 
(list 640.1049 -266.525) 
(list 640.1066 -264.8667) 
(list 640.1083 -263.2083) 
(list 640.1101 -261.55) 
(list 640.112 -259.8917) 
(list 640.1139 -258.2333) 
(list 640.1158 -256.575) 
(list 640.1177 -254.9167) 
(list 640.1198 -253.2583) 
(list 640.1218 -251.6) 
(list 640.1239 -249.9417) 
(list 640.126 -248.2833) 
(list 640.1282 -246.625) 
(list 640.1304 -244.9667) 
(list 640.1327 -243.3083) 
(list 640.135 -241.65) 
(list 640.1374 -239.9917) 
(list 640.1398 -238.3333) 
(list 640.1423 -236.675) 
(list 640.1448 -235.0167) 
(list 640.1473 -233.3583) 
(list 640.1499 -231.7) 
(list 640.1526 -230.0417) 
(list 640.1552 -228.3833) 
(list 640.158 -226.725) 
(list 640.1608 -225.0667) 
(list 640.1636 -223.4083) 
(list 640.1665 -221.75) 
(list 640.1695 -220.0917) 
(list 640.1725 -218.4333) 
(list 640.1755 -216.775) 
(list 640.1786 -215.1167) 
(list 640.1818 -213.4583) 
(list 640.185 -211.8) 
(list 639.815 -211.8) 
(list 639.8182 -213.4583) 
(list 639.8214 -215.1167) 
(list 639.8245 -216.775) 
(list 639.8275 -218.4333) 
(list 639.8305 -220.0917) 
(list 639.8335 -221.75) 
(list 639.8364 -223.4083) 
(list 639.8392 -225.0667) 
(list 639.842 -226.725) 
(list 639.8448 -228.3833) 
(list 639.8474 -230.0417) 
(list 639.8501 -231.7) 
(list 639.8527 -233.3583) 
(list 639.8552 -235.0167) 
(list 639.8577 -236.675) 
(list 639.8602 -238.3333) 
(list 639.8626 -239.9917) 
(list 639.865 -241.65) 
(list 639.8673 -243.3083) 
(list 639.8696 -244.9667) 
(list 639.8718 -246.625) 
(list 639.874 -248.2833) 
(list 639.8761 -249.9417) 
(list 639.8782 -251.6) 
(list 639.8802 -253.2583) 
(list 639.8823 -254.9167) 
(list 639.8842 -256.575) 
(list 639.8861 -258.2333) 
(list 639.888 -259.8917) 
(list 639.8899 -261.55) 
(list 639.8917 -263.2083) 
(list 639.8934 -264.8667) 
(list 639.8951 -266.525) 
(list 639.8968 -268.1833) 
(list 639.8985 -269.8417) 
(list 639.9001 -271.5) 
(list 639.9016 -273.1583) 
(list 639.9032 -274.8167) 
(list 639.9047 -276.475) 
(list 639.9061 -278.1333) 
(list 639.9076 -279.7917) 
(list 639.9089 -281.45) 
(list 639.9103 -283.1083) 
(list 639.9116 -284.7667) 
(list 639.9129 -286.425) 
(list 639.9141 -288.0833) 
(list 639.9153 -289.7417) 
(list 639.9165 -291.4) 
(list 639.9177 -293.0583) 
(list 639.9188 -294.7167) 
(list 639.9199 -296.375) 
(list 639.9209 -298.0333) 
(list 639.922 -299.6917) 
(list 639.923 -301.35) 
(list 639.9239 -303.0083) 
(list 639.9249 -304.6667) 
(list 639.9258 -306.325) 
(list 639.9266 -307.9833) 
(list 639.9275 -309.6417) 
(list 639.9283 -311.3) 
(list 639.9291 -312.9583) 
(list 639.9299 -314.6167) 
(list 639.9306 -316.275) 
(list 639.9313 -317.9333) 
(list 639.932 -319.5917) 
(list 639.9327 -321.25) 
(list 639.9333 -322.9083) 
(list 639.934 -324.5667) 
(list 639.9346 -326.225) 
(list 639.9351 -327.8833) 
(list 639.9357 -329.5417) 
(list 639.9362 -331.2) 
(list 639.9367 -332.8583) 
(list 639.9372 -334.5167) 
(list 639.9377 -336.175) 
(list 639.9381 -337.8333) 
(list 639.9385 -339.4917) 
(list 639.9389 -341.15) 
(list 639.9393 -342.8083) 
(list 639.9397 -344.4667) 
(list 639.9401 -346.125) 
(list 639.9404 -347.7833) 
(list 639.9407 -349.4417) 
(list 639.941 -351.1) 
(list 639.9413 -352.7583) 
(list 639.9416 -354.4167) 
(list 639.9418 -356.075) 
(list 639.942 -357.7333) 
(list 639.9423 -359.3917) 
(list 639.9425 -361.05) 
(list 639.9427 -362.7083) 
(list 639.9429 -364.3667) 
(list 639.943 -366.025) 
(list 639.9432 -367.6833) 
(list 639.9433 -369.3417) 
(list 639.9435 -371) 
(list 639.9436 -372.6583) 
(list 639.9437 -374.3167) 
(list 639.9438 -375.975) 
(list 639.9439 -377.6333) 
(list 639.944 -379.2917) 
(list 639.9441 -380.95) 
(list 639.9441 -382.6083) 
(list 639.9442 -384.2667) 
(list 639.9442 -385.925) 
(list 639.9443 -387.5833) 
(list 639.9443 -389.2417) 
(list 639.9444 -390.9) 
(list 639.9444 -392.5583) 
(list 639.9444 -394.2167) 
(list 639.9444 -395.875) 
(list 639.9445 -397.5333) 
(list 639.9445 -399.1917) 
(list 639.9445 -400.85) 
(list 639.9445 -402.5083) 
(list 639.9445 -404.1667) 
(list 639.9445 -405.825) 
(list 639.9445 -407.4833) 
(list 639.9445 -409.1417) 
(list 639.9445 -410.8)))
(apply 'command (append '("pline") coords '("c")))
(setq currobj (ssadd (entlast) currobj))
(command "_layer" "set" "prebias" "")
(command "_rectangle" "639.815,-410.8" "640.185,-211.8")
(setq currobj (ssadd (entlast) currobj))
(command "_layer" "set" "nitride" "")
(setq singlenanobeam2 currobj)
(setq currobj nil)
(setq currobj (ssadd))
; DRAWING NODE ARRAY
(setq coords (list 
(list 640.185 -211.8) 
(list 640.5625 -201.8) 
(list 640.5625 -201.8) 
(list 640.5625 -200.8) 
(list 714.585 -212.6864) 
(list 714.585 -207.7434) 
(list 640.5625 -197.357) 
(list 640.5625 -196.357) 
(list 640.5625 -196.357) 
(list 640.2625 -186.357) 
(list 639.7375 -186.357) 
(list 639.4375 -196.357) 
(list 639.4375 -196.357) 
(list 639.4375 -197.357) 
(list 565.415 -207.7434) 
(list 565.415 -212.6864) 
(list 639.4375 -200.8) 
(list 639.4375 -201.8) 
(list 639.4375 -201.8) 
(list 639.815 -211.8)))
(apply 'command (append '("pline") coords '("c")))
(setq currobj (ssadd (entlast) currobj))
(command "_layer" "set" "prebias" "")
(setq coords (list 
(list 639.4375 -212.6864) 
(list 639.4375 -200.8) 
(list 565.415 -212.6864) 
(list 565.415 -207.7434) 
(list 639.4375 -197.357) 
(list 639.4375 -186.357) 
(list 640.5625 -186.357) 
(list 640.5625 -197.357) 
(list 714.585 -207.7434) 
(list 714.585 -212.6864) 
(list 640.5625 -200.8) 
(list 640.5625 -212.6864)))
(apply 'command (append '("pline") coords '("c")))
(setq currobj (ssadd (entlast) currobj))
(command "_layer" "set" "nitride" "")
(command "_layer" "set" "fda1" "")
(setq coords (list 
(list 640.5625 -200.657) 
(list 714.585 -212.5434) 
(list 714.585 -212.3664) 
(list 640.5625 -200.58)))
(apply 'command (append '("pline") coords '("c")))
(setq currobj (ssadd (entlast) currobj))
(setq coords (list 
(list 640.5625 -200.437) 
(list 714.585 -212.2234) 
(list 714.585 -212.0464) 
(list 640.5625 -200.36)))
(apply 'command (append '("pline") coords '("c")))
(setq currobj (ssadd (entlast) currobj))
(setq coords (list 
(list 640.5625 -200.217) 
(list 714.585 -211.9034) 
(list 714.585 -211.7264) 
(list 640.5625 -200.14)))
(apply 'command (append '("pline") coords '("c")))
(setq currobj (ssadd (entlast) currobj))
(setq coords (list 
(list 640.5625 -199.997) 
(list 714.585 -211.5834) 
(list 714.585 -211.4064) 
(list 640.5625 -199.92)))
(apply 'command (append '("pline") coords '("c")))
(setq currobj (ssadd (entlast) currobj))
(setq coords (list 
(list 640.5625 -199.777) 
(list 714.585 -211.2634) 
(list 714.585 -211.0864) 
(list 640.5625 -199.7)))
(apply 'command (append '("pline") coords '("c")))
(setq currobj (ssadd (entlast) currobj))
(setq coords (list 
(list 640.5625 -199.557) 
(list 714.585 -210.9434) 
(list 714.585 -210.7664) 
(list 640.5625 -199.48)))
(apply 'command (append '("pline") coords '("c")))
(setq currobj (ssadd (entlast) currobj))
(setq coords (list 
(list 640.5625 -199.337) 
(list 714.585 -210.6234) 
(list 714.585 -210.4464) 
(list 640.5625 -199.26)))
(apply 'command (append '("pline") coords '("c")))
(setq currobj (ssadd (entlast) currobj))
(setq coords (list 
(list 640.5625 -199.117) 
(list 714.585 -210.3034) 
(list 714.585 -210.1264) 
(list 640.5625 -199.04)))
(apply 'command (append '("pline") coords '("c")))
(setq currobj (ssadd (entlast) currobj))
(setq coords (list 
(list 640.5625 -198.897) 
(list 714.585 -209.9834) 
(list 714.585 -209.8064) 
(list 640.5625 -198.82)))
(apply 'command (append '("pline") coords '("c")))
(setq currobj (ssadd (entlast) currobj))
(setq coords (list 
(list 640.5625 -198.677) 
(list 714.585 -209.6634) 
(list 714.585 -209.4864) 
(list 640.5625 -198.6)))
(apply 'command (append '("pline") coords '("c")))
(setq currobj (ssadd (entlast) currobj))
(setq coords (list 
(list 640.5625 -198.457) 
(list 714.585 -209.3434) 
(list 714.585 -209.1664) 
(list 640.5625 -198.38)))
(apply 'command (append '("pline") coords '("c")))
(setq currobj (ssadd (entlast) currobj))
(setq coords (list 
(list 640.5625 -198.237) 
(list 714.585 -209.0234) 
(list 714.585 -208.8464) 
(list 640.5625 -198.16)))
(apply 'command (append '("pline") coords '("c")))
(setq currobj (ssadd (entlast) currobj))
(setq coords (list 
(list 640.5625 -198.017) 
(list 714.585 -208.7034) 
(list 714.585 -208.5264) 
(list 640.5625 -197.94)))
(apply 'command (append '("pline") coords '("c")))
(setq currobj (ssadd (entlast) currobj))
(setq coords (list 
(list 640.5625 -197.797) 
(list 714.585 -208.3834) 
(list 714.585 -208.2064) 
(list 640.5625 -197.72)))
(apply 'command (append '("pline") coords '("c")))
(setq currobj (ssadd (entlast) currobj))
(setq coords (list 
(list 640.5625 -197.577) 
(list 714.585 -208.0634) 
(list 714.585 -207.8864) 
(list 640.5625 -197.5)))
(apply 'command (append '("pline") coords '("c")))
(setq currobj (ssadd (entlast) currobj))
(setq coords (list 
(list 639.4375 -197.5) 
(list 565.415 -207.8864) 
(list 565.415 -208.0634) 
(list 639.4375 -197.577)))
(apply 'command (append '("pline") coords '("c")))
(setq currobj (ssadd (entlast) currobj))
(setq coords (list 
(list 639.4375 -197.72) 
(list 565.415 -208.2064) 
(list 565.415 -208.3834) 
(list 639.4375 -197.797)))
(apply 'command (append '("pline") coords '("c")))
(setq currobj (ssadd (entlast) currobj))
(setq coords (list 
(list 639.4375 -197.94) 
(list 565.415 -208.5264) 
(list 565.415 -208.7034) 
(list 639.4375 -198.017)))
(apply 'command (append '("pline") coords '("c")))
(setq currobj (ssadd (entlast) currobj))
(setq coords (list 
(list 639.4375 -198.16) 
(list 565.415 -208.8464) 
(list 565.415 -209.0234) 
(list 639.4375 -198.237)))
(apply 'command (append '("pline") coords '("c")))
(setq currobj (ssadd (entlast) currobj))
(setq coords (list 
(list 639.4375 -198.38) 
(list 565.415 -209.1664) 
(list 565.415 -209.3434) 
(list 639.4375 -198.457)))
(apply 'command (append '("pline") coords '("c")))
(setq currobj (ssadd (entlast) currobj))
(setq coords (list 
(list 639.4375 -198.6) 
(list 565.415 -209.4864) 
(list 565.415 -209.6634) 
(list 639.4375 -198.677)))
(apply 'command (append '("pline") coords '("c")))
(setq currobj (ssadd (entlast) currobj))
(setq coords (list 
(list 639.4375 -198.82) 
(list 565.415 -209.8064) 
(list 565.415 -209.9834) 
(list 639.4375 -198.897)))
(apply 'command (append '("pline") coords '("c")))
(setq currobj (ssadd (entlast) currobj))
(setq coords (list 
(list 639.4375 -199.04) 
(list 565.415 -210.1264) 
(list 565.415 -210.3034) 
(list 639.4375 -199.117)))
(apply 'command (append '("pline") coords '("c")))
(setq currobj (ssadd (entlast) currobj))
(setq coords (list 
(list 639.4375 -199.26) 
(list 565.415 -210.4464) 
(list 565.415 -210.6234) 
(list 639.4375 -199.337)))
(apply 'command (append '("pline") coords '("c")))
(setq currobj (ssadd (entlast) currobj))
(setq coords (list 
(list 639.4375 -199.48) 
(list 565.415 -210.7664) 
(list 565.415 -210.9434) 
(list 639.4375 -199.557)))
(apply 'command (append '("pline") coords '("c")))
(setq currobj (ssadd (entlast) currobj))
(setq coords (list 
(list 639.4375 -199.7) 
(list 565.415 -211.0864) 
(list 565.415 -211.2634) 
(list 639.4375 -199.777)))
(apply 'command (append '("pline") coords '("c")))
(setq currobj (ssadd (entlast) currobj))
(setq coords (list 
(list 639.4375 -199.92) 
(list 565.415 -211.4064) 
(list 565.415 -211.5834) 
(list 639.4375 -199.997)))
(apply 'command (append '("pline") coords '("c")))
(setq currobj (ssadd (entlast) currobj))
(setq coords (list 
(list 639.4375 -200.14) 
(list 565.415 -211.7264) 
(list 565.415 -211.9034) 
(list 639.4375 -200.217)))
(apply 'command (append '("pline") coords '("c")))
(setq currobj (ssadd (entlast) currobj))
(setq coords (list 
(list 639.4375 -200.36) 
(list 565.415 -212.0464) 
(list 565.415 -212.2234) 
(list 639.4375 -200.437)))
(apply 'command (append '("pline") coords '("c")))
(setq currobj (ssadd (entlast) currobj))
(setq coords (list 
(list 639.4375 -200.58) 
(list 565.415 -212.3664) 
(list 565.415 -212.5434) 
(list 639.4375 -200.657)))
(apply 'command (append '("pline") coords '("c")))
(setq currobj (ssadd (entlast) currobj))
(command "_layer" "set" "nitride" "")
(command "_layer" "set" "text" "")
(command "_circle" "638.985,-211.8" "0.075")
(command "_circle" "638.985,-211.5" "0.075")
(command "_circle" "638.985,-211.2" "0.075")
(command "_circle" "638.985,-210.9" "0.075")
(command "_circle" "638.985,-210.6" "0.075")
(command "_circle" "638.685,-211.8" "0.075")
(command "_circle" "638.685,-211.5" "0.075")
(command "_circle" "638.685,-211.2" "0.075")
(command "_circle" "638.685,-210.9" "0.075")
(command "_circle" "638.685,-210.6" "0.075")
(command "_circle" "638.385,-211.8" "0.075")
(command "_circle" "638.385,-211.5" "0.075")
(command "_circle" "638.385,-211.2" "0.075")
(command "_circle" "638.385,-210.9" "0.075")
(command "_circle" "638.385,-210.6" "0.075")
(command "_circle" "638.085,-211.8" "0.075")
(command "_circle" "638.085,-211.5" "0.075")
(command "_circle" "638.085,-211.2" "0.075")
(command "_circle" "638.085,-210.9" "0.075")
(command "_circle" "638.085,-210.6" "0.075")
(command "_circle" "637.785,-211.8" "0.075")
(command "_circle" "637.785,-211.5" "0.075")
(command "_circle" "637.785,-211.2" "0.075")
(command "_circle" "637.785,-210.9" "0.075")
(command "_circle" "637.785,-210.6" "0.075")
(command "_layer" "set" "nitride" "")
(setq anglednodearray2 currobj)
(setq currobj nil)
(setq currobj (ssadd))
; DRAWING COOLED SINGLE NANOBEAM
(setq coords (list 
(list 640.2625 -186.357) 
(list 640.2625 -181.357) 
(list 639.7375 -181.357) 
(list 639.7375 -186.357)))
(apply 'command (append '("pline") coords '("c")))
(setq currobj (ssadd (entlast) currobj))
(command "_layer" "set" "prebias" "")
(command "_rectangle" "639.7375,-186.357" "640.2625,-181.357")
(setq currobj (ssadd (entlast) currobj))
(command "_layer" "set" "nitride" "")
(setq coords (list 
(list 640.2625 -181.357) 
(list 640.5625 -171.357) 
(list 640.5625 -171.357) 
(list 640.5625 -170.357) 
(list 714.585 -171.107) 
(list 714.585 -166.164) 
(list 640.5625 -166.914) 
(list 640.5625 -165.914) 
(list 640.5625 -165.914) 
(list 640.2625 -155.914) 
(list 639.7375 -155.914) 
(list 639.4375 -165.914) 
(list 639.4375 -165.914) 
(list 639.4375 -166.914) 
(list 565.415 -166.164) 
(list 565.415 -171.107) 
(list 639.4375 -170.357) 
(list 639.4375 -171.357) 
(list 639.4375 -171.357) 
(list 639.7375 -181.357)))
(apply 'command (append '("pline") coords '("c")))
(setq currobj (ssadd (entlast) currobj))
(command "_layer" "set" "prebias" "")
(setq coords (list 
(list 639.4375 -181.357) 
(list 639.4375 -170.357) 
(list 565.415 -171.107) 
(list 565.415 -166.164) 
(list 639.4375 -166.914) 
(list 639.4375 -155.914) 
(list 640.5625 -155.914) 
(list 640.5625 -166.914) 
(list 714.585 -166.164) 
(list 714.585 -171.107) 
(list 640.5625 -170.357) 
(list 640.5625 -181.357)))
(apply 'command (append '("pline") coords '("c")))
(setq currobj (ssadd (entlast) currobj))
(command "_layer" "set" "nitride" "")
(command "_layer" "set" "fda1" "")
(setq coords (list 
(list 640.5625 -170.214) 
(list 714.585 -170.964) 
(list 714.585 -170.787) 
(list 640.5625 -170.137)))
(apply 'command (append '("pline") coords '("c")))
(setq currobj (ssadd (entlast) currobj))
(setq coords (list 
(list 640.5625 -169.994) 
(list 714.585 -170.644) 
(list 714.585 -170.467) 
(list 640.5625 -169.917)))
(apply 'command (append '("pline") coords '("c")))
(setq currobj (ssadd (entlast) currobj))
(setq coords (list 
(list 640.5625 -169.774) 
(list 714.585 -170.324) 
(list 714.585 -170.147) 
(list 640.5625 -169.697)))
(apply 'command (append '("pline") coords '("c")))
(setq currobj (ssadd (entlast) currobj))
(setq coords (list 
(list 640.5625 -169.554) 
(list 714.585 -170.004) 
(list 714.585 -169.827) 
(list 640.5625 -169.477)))
(apply 'command (append '("pline") coords '("c")))
(setq currobj (ssadd (entlast) currobj))
(setq coords (list 
(list 640.5625 -169.334) 
(list 714.585 -169.684) 
(list 714.585 -169.507) 
(list 640.5625 -169.257)))
(apply 'command (append '("pline") coords '("c")))
(setq currobj (ssadd (entlast) currobj))
(setq coords (list 
(list 640.5625 -169.114) 
(list 714.585 -169.364) 
(list 714.585 -169.187) 
(list 640.5625 -169.037)))
(apply 'command (append '("pline") coords '("c")))
(setq currobj (ssadd (entlast) currobj))
(setq coords (list 
(list 640.5625 -168.894) 
(list 714.585 -169.044) 
(list 714.585 -168.867) 
(list 640.5625 -168.817)))
(apply 'command (append '("pline") coords '("c")))
(setq currobj (ssadd (entlast) currobj))
(setq coords (list 
(list 640.5625 -168.674) 
(list 714.585 -168.724) 
(list 714.585 -168.547) 
(list 640.5625 -168.597)))
(apply 'command (append '("pline") coords '("c")))
(setq currobj (ssadd (entlast) currobj))
(setq coords (list 
(list 640.5625 -168.454) 
(list 714.585 -168.404) 
(list 714.585 -168.227) 
(list 640.5625 -168.377)))
(apply 'command (append '("pline") coords '("c")))
(setq currobj (ssadd (entlast) currobj))
(setq coords (list 
(list 640.5625 -168.234) 
(list 714.585 -168.084) 
(list 714.585 -167.907) 
(list 640.5625 -168.157)))
(apply 'command (append '("pline") coords '("c")))
(setq currobj (ssadd (entlast) currobj))
(setq coords (list 
(list 640.5625 -168.014) 
(list 714.585 -167.764) 
(list 714.585 -167.587) 
(list 640.5625 -167.937)))
(apply 'command (append '("pline") coords '("c")))
(setq currobj (ssadd (entlast) currobj))
(setq coords (list 
(list 640.5625 -167.794) 
(list 714.585 -167.444) 
(list 714.585 -167.267) 
(list 640.5625 -167.717)))
(apply 'command (append '("pline") coords '("c")))
(setq currobj (ssadd (entlast) currobj))
(setq coords (list 
(list 640.5625 -167.574) 
(list 714.585 -167.124) 
(list 714.585 -166.947) 
(list 640.5625 -167.497)))
(apply 'command (append '("pline") coords '("c")))
(setq currobj (ssadd (entlast) currobj))
(setq coords (list 
(list 640.5625 -167.354) 
(list 714.585 -166.804) 
(list 714.585 -166.627) 
(list 640.5625 -167.277)))
(apply 'command (append '("pline") coords '("c")))
(setq currobj (ssadd (entlast) currobj))
(setq coords (list 
(list 640.5625 -167.134) 
(list 714.585 -166.484) 
(list 714.585 -166.307) 
(list 640.5625 -167.057)))
(apply 'command (append '("pline") coords '("c")))
(setq currobj (ssadd (entlast) currobj))
(setq coords (list 
(list 639.4375 -167.057) 
(list 565.415 -166.307) 
(list 565.415 -166.484) 
(list 639.4375 -167.134)))
(apply 'command (append '("pline") coords '("c")))
(setq currobj (ssadd (entlast) currobj))
(setq coords (list 
(list 639.4375 -167.277) 
(list 565.415 -166.627) 
(list 565.415 -166.804) 
(list 639.4375 -167.354)))
(apply 'command (append '("pline") coords '("c")))
(setq currobj (ssadd (entlast) currobj))
(setq coords (list 
(list 639.4375 -167.497) 
(list 565.415 -166.947) 
(list 565.415 -167.124) 
(list 639.4375 -167.574)))
(apply 'command (append '("pline") coords '("c")))
(setq currobj (ssadd (entlast) currobj))
(setq coords (list 
(list 639.4375 -167.717) 
(list 565.415 -167.267) 
(list 565.415 -167.444) 
(list 639.4375 -167.794)))
(apply 'command (append '("pline") coords '("c")))
(setq currobj (ssadd (entlast) currobj))
(setq coords (list 
(list 639.4375 -167.937) 
(list 565.415 -167.587) 
(list 565.415 -167.764) 
(list 639.4375 -168.014)))
(apply 'command (append '("pline") coords '("c")))
(setq currobj (ssadd (entlast) currobj))
(setq coords (list 
(list 639.4375 -168.157) 
(list 565.415 -167.907) 
(list 565.415 -168.084) 
(list 639.4375 -168.234)))
(apply 'command (append '("pline") coords '("c")))
(setq currobj (ssadd (entlast) currobj))
(setq coords (list 
(list 639.4375 -168.377) 
(list 565.415 -168.227) 
(list 565.415 -168.404) 
(list 639.4375 -168.454)))
(apply 'command (append '("pline") coords '("c")))
(setq currobj (ssadd (entlast) currobj))
(setq coords (list 
(list 639.4375 -168.597) 
(list 565.415 -168.547) 
(list 565.415 -168.724) 
(list 639.4375 -168.674)))
(apply 'command (append '("pline") coords '("c")))
(setq currobj (ssadd (entlast) currobj))
(setq coords (list 
(list 639.4375 -168.817) 
(list 565.415 -168.867) 
(list 565.415 -169.044) 
(list 639.4375 -168.894)))
(apply 'command (append '("pline") coords '("c")))
(setq currobj (ssadd (entlast) currobj))
(setq coords (list 
(list 639.4375 -169.037) 
(list 565.415 -169.187) 
(list 565.415 -169.364) 
(list 639.4375 -169.114)))
(apply 'command (append '("pline") coords '("c")))
(setq currobj (ssadd (entlast) currobj))
(setq coords (list 
(list 639.4375 -169.257) 
(list 565.415 -169.507) 
(list 565.415 -169.684) 
(list 639.4375 -169.334)))
(apply 'command (append '("pline") coords '("c")))
(setq currobj (ssadd (entlast) currobj))
(setq coords (list 
(list 639.4375 -169.477) 
(list 565.415 -169.827) 
(list 565.415 -170.004) 
(list 639.4375 -169.554)))
(apply 'command (append '("pline") coords '("c")))
(setq currobj (ssadd (entlast) currobj))
(setq coords (list 
(list 639.4375 -169.697) 
(list 565.415 -170.147) 
(list 565.415 -170.324) 
(list 639.4375 -169.774)))
(apply 'command (append '("pline") coords '("c")))
(setq currobj (ssadd (entlast) currobj))
(setq coords (list 
(list 639.4375 -169.917) 
(list 565.415 -170.467) 
(list 565.415 -170.644) 
(list 639.4375 -169.994)))
(apply 'command (append '("pline") coords '("c")))
(setq currobj (ssadd (entlast) currobj))
(setq coords (list 
(list 639.4375 -170.137) 
(list 565.415 -170.787) 
(list 565.415 -170.964) 
(list 639.4375 -170.214)))
(apply 'command (append '("pline") coords '("c")))
(setq currobj (ssadd (entlast) currobj))
(command "_layer" "set" "nitride" "")
(command "_layer" "set" "text" "")
(command "_circle" "639.0625,-181.357" "0.075")
(command "_circle" "639.0625,-181.057" "0.075")
(command "_circle" "639.0625,-180.757" "0.075")
(command "_circle" "639.0625,-180.457" "0.075")
(command "_circle" "639.0625,-180.157" "0.075")
(command "_circle" "638.7625,-181.357" "0.075")
(command "_circle" "638.7625,-181.057" "0.075")
(command "_circle" "638.7625,-180.757" "0.075")
(command "_circle" "638.7625,-180.457" "0.075")
(command "_circle" "638.7625,-180.157" "0.075")
(command "_circle" "638.4625,-181.357" "0.075")
(command "_circle" "638.4625,-181.057" "0.075")
(command "_circle" "638.4625,-180.757" "0.075")
(command "_circle" "638.4625,-180.457" "0.075")
(command "_circle" "638.4625,-180.157" "0.075")
(command "_circle" "638.1625,-181.357" "0.075")
(command "_circle" "638.1625,-181.057" "0.075")
(command "_circle" "638.1625,-180.757" "0.075")
(command "_circle" "638.1625,-180.457" "0.075")
(command "_circle" "638.1625,-180.157" "0.075")
(command "_circle" "637.8625,-181.357" "0.075")
(command "_circle" "637.8625,-181.057" "0.075")
(command "_circle" "637.8625,-180.757" "0.075")
(command "_circle" "637.8625,-180.457" "0.075")
(command "_circle" "637.8625,-180.157" "0.075")
(command "_layer" "set" "nitride" "")
(setq coords (list 
(list 640.2625 -155.914) 
(list 640.2625 -40.2693) 
(list 639.7375 -40.2693) 
(list 639.7375 -155.914)))
(apply 'command (append '("pline") coords '("c")))
(setq currobj (ssadd (entlast) currobj))
(command "_layer" "set" "prebias" "")
(command "_rectangle" "639.7375,-155.914" "640.2625,-40.2693")
(setq currobj (ssadd (entlast) currobj))
(command "_layer" "set" "nitride" "")
(setq coords (list 
(list 640.2625 -40.2693) 
(list 640.5625 -30.2693) 
(list 640.5625 -30.2693) 
(list 640.5625 -29.2693) 
(list 714.585 -30.0193) 
(list 714.585 -25.0763) 
(list 640.5625 -25.8263) 
(list 640.5625 -24.8263) 
(list 640.5625 -24.8263) 
(list 640.2625 -14.8263) 
(list 639.7375 -14.8263) 
(list 639.4375 -24.8263) 
(list 639.4375 -24.8263) 
(list 639.4375 -25.8263) 
(list 565.415 -25.0763) 
(list 565.415 -30.0193) 
(list 639.4375 -29.2693) 
(list 639.4375 -30.2693) 
(list 639.4375 -30.2693) 
(list 639.7375 -40.2693)))
(apply 'command (append '("pline") coords '("c")))
(setq currobj (ssadd (entlast) currobj))
(command "_layer" "set" "prebias" "")
(setq coords (list 
(list 639.4375 -40.2693) 
(list 639.4375 -29.2693) 
(list 565.415 -30.0193) 
(list 565.415 -25.0763) 
(list 639.4375 -25.8263) 
(list 639.4375 -14.8263) 
(list 640.5625 -14.8263) 
(list 640.5625 -25.8263) 
(list 714.585 -25.0763) 
(list 714.585 -30.0193) 
(list 640.5625 -29.2693) 
(list 640.5625 -40.2693)))
(apply 'command (append '("pline") coords '("c")))
(setq currobj (ssadd (entlast) currobj))
(command "_layer" "set" "nitride" "")
(command "_layer" "set" "fda1" "")
(setq coords (list 
(list 640.5625 -29.1263) 
(list 714.585 -29.8763) 
(list 714.585 -29.6993) 
(list 640.5625 -29.0493)))
(apply 'command (append '("pline") coords '("c")))
(setq currobj (ssadd (entlast) currobj))
(setq coords (list 
(list 640.5625 -28.9063) 
(list 714.585 -29.5563) 
(list 714.585 -29.3793) 
(list 640.5625 -28.8293)))
(apply 'command (append '("pline") coords '("c")))
(setq currobj (ssadd (entlast) currobj))
(setq coords (list 
(list 640.5625 -28.6863) 
(list 714.585 -29.2363) 
(list 714.585 -29.0593) 
(list 640.5625 -28.6093)))
(apply 'command (append '("pline") coords '("c")))
(setq currobj (ssadd (entlast) currobj))
(setq coords (list 
(list 640.5625 -28.4663) 
(list 714.585 -28.9163) 
(list 714.585 -28.7393) 
(list 640.5625 -28.3893)))
(apply 'command (append '("pline") coords '("c")))
(setq currobj (ssadd (entlast) currobj))
(setq coords (list 
(list 640.5625 -28.2463) 
(list 714.585 -28.5963) 
(list 714.585 -28.4193) 
(list 640.5625 -28.1693)))
(apply 'command (append '("pline") coords '("c")))
(setq currobj (ssadd (entlast) currobj))
(setq coords (list 
(list 640.5625 -28.0263) 
(list 714.585 -28.2763) 
(list 714.585 -28.0993) 
(list 640.5625 -27.9493)))
(apply 'command (append '("pline") coords '("c")))
(setq currobj (ssadd (entlast) currobj))
(setq coords (list 
(list 640.5625 -27.8063) 
(list 714.585 -27.9563) 
(list 714.585 -27.7793) 
(list 640.5625 -27.7293)))
(apply 'command (append '("pline") coords '("c")))
(setq currobj (ssadd (entlast) currobj))
(setq coords (list 
(list 640.5625 -27.5863) 
(list 714.585 -27.6363) 
(list 714.585 -27.4593) 
(list 640.5625 -27.5093)))
(apply 'command (append '("pline") coords '("c")))
(setq currobj (ssadd (entlast) currobj))
(setq coords (list 
(list 640.5625 -27.3663) 
(list 714.585 -27.3163) 
(list 714.585 -27.1393) 
(list 640.5625 -27.2893)))
(apply 'command (append '("pline") coords '("c")))
(setq currobj (ssadd (entlast) currobj))
(setq coords (list 
(list 640.5625 -27.1463) 
(list 714.585 -26.9963) 
(list 714.585 -26.8193) 
(list 640.5625 -27.0693)))
(apply 'command (append '("pline") coords '("c")))
(setq currobj (ssadd (entlast) currobj))
(setq coords (list 
(list 640.5625 -26.9263) 
(list 714.585 -26.6763) 
(list 714.585 -26.4993) 
(list 640.5625 -26.8493)))
(apply 'command (append '("pline") coords '("c")))
(setq currobj (ssadd (entlast) currobj))
(setq coords (list 
(list 640.5625 -26.7063) 
(list 714.585 -26.3563) 
(list 714.585 -26.1793) 
(list 640.5625 -26.6293)))
(apply 'command (append '("pline") coords '("c")))
(setq currobj (ssadd (entlast) currobj))
(setq coords (list 
(list 640.5625 -26.4863) 
(list 714.585 -26.0363) 
(list 714.585 -25.8593) 
(list 640.5625 -26.4093)))
(apply 'command (append '("pline") coords '("c")))
(setq currobj (ssadd (entlast) currobj))
(setq coords (list 
(list 640.5625 -26.2663) 
(list 714.585 -25.7163) 
(list 714.585 -25.5393) 
(list 640.5625 -26.1893)))
(apply 'command (append '("pline") coords '("c")))
(setq currobj (ssadd (entlast) currobj))
(setq coords (list 
(list 640.5625 -26.0463) 
(list 714.585 -25.3963) 
(list 714.585 -25.2193) 
(list 640.5625 -25.9693)))
(apply 'command (append '("pline") coords '("c")))
(setq currobj (ssadd (entlast) currobj))
(setq coords (list 
(list 639.4375 -25.9693) 
(list 565.415 -25.2193) 
(list 565.415 -25.3963) 
(list 639.4375 -26.0463)))
(apply 'command (append '("pline") coords '("c")))
(setq currobj (ssadd (entlast) currobj))
(setq coords (list 
(list 639.4375 -26.1893) 
(list 565.415 -25.5393) 
(list 565.415 -25.7163) 
(list 639.4375 -26.2663)))
(apply 'command (append '("pline") coords '("c")))
(setq currobj (ssadd (entlast) currobj))
(setq coords (list 
(list 639.4375 -26.4093) 
(list 565.415 -25.8593) 
(list 565.415 -26.0363) 
(list 639.4375 -26.4863)))
(apply 'command (append '("pline") coords '("c")))
(setq currobj (ssadd (entlast) currobj))
(setq coords (list 
(list 639.4375 -26.6293) 
(list 565.415 -26.1793) 
(list 565.415 -26.3563) 
(list 639.4375 -26.7063)))
(apply 'command (append '("pline") coords '("c")))
(setq currobj (ssadd (entlast) currobj))
(setq coords (list 
(list 639.4375 -26.8493) 
(list 565.415 -26.4993) 
(list 565.415 -26.6763) 
(list 639.4375 -26.9263)))
(apply 'command (append '("pline") coords '("c")))
(setq currobj (ssadd (entlast) currobj))
(setq coords (list 
(list 639.4375 -27.0693) 
(list 565.415 -26.8193) 
(list 565.415 -26.9963) 
(list 639.4375 -27.1463)))
(apply 'command (append '("pline") coords '("c")))
(setq currobj (ssadd (entlast) currobj))
(setq coords (list 
(list 639.4375 -27.2893) 
(list 565.415 -27.1393) 
(list 565.415 -27.3163) 
(list 639.4375 -27.3663)))
(apply 'command (append '("pline") coords '("c")))
(setq currobj (ssadd (entlast) currobj))
(setq coords (list 
(list 639.4375 -27.5093) 
(list 565.415 -27.4593) 
(list 565.415 -27.6363) 
(list 639.4375 -27.5863)))
(apply 'command (append '("pline") coords '("c")))
(setq currobj (ssadd (entlast) currobj))
(setq coords (list 
(list 639.4375 -27.7293) 
(list 565.415 -27.7793) 
(list 565.415 -27.9563) 
(list 639.4375 -27.8063)))
(apply 'command (append '("pline") coords '("c")))
(setq currobj (ssadd (entlast) currobj))
(setq coords (list 
(list 639.4375 -27.9493) 
(list 565.415 -28.0993) 
(list 565.415 -28.2763) 
(list 639.4375 -28.0263)))
(apply 'command (append '("pline") coords '("c")))
(setq currobj (ssadd (entlast) currobj))
(setq coords (list 
(list 639.4375 -28.1693) 
(list 565.415 -28.4193) 
(list 565.415 -28.5963) 
(list 639.4375 -28.2463)))
(apply 'command (append '("pline") coords '("c")))
(setq currobj (ssadd (entlast) currobj))
(setq coords (list 
(list 639.4375 -28.3893) 
(list 565.415 -28.7393) 
(list 565.415 -28.9163) 
(list 639.4375 -28.4663)))
(apply 'command (append '("pline") coords '("c")))
(setq currobj (ssadd (entlast) currobj))
(setq coords (list 
(list 639.4375 -28.6093) 
(list 565.415 -29.0593) 
(list 565.415 -29.2363) 
(list 639.4375 -28.6863)))
(apply 'command (append '("pline") coords '("c")))
(setq currobj (ssadd (entlast) currobj))
(setq coords (list 
(list 639.4375 -28.8293) 
(list 565.415 -29.3793) 
(list 565.415 -29.5563) 
(list 639.4375 -28.9063)))
(apply 'command (append '("pline") coords '("c")))
(setq currobj (ssadd (entlast) currobj))
(setq coords (list 
(list 639.4375 -29.0493) 
(list 565.415 -29.6993) 
(list 565.415 -29.8763) 
(list 639.4375 -29.1263)))
(apply 'command (append '("pline") coords '("c")))
(setq currobj (ssadd (entlast) currobj))
(command "_layer" "set" "nitride" "")
(command "_layer" "set" "text" "")
(command "_circle" "639.0625,-40.2693" "0.075")
(command "_circle" "639.0625,-39.9693" "0.075")
(command "_circle" "639.0625,-39.6693" "0.075")
(command "_circle" "639.0625,-39.3693" "0.075")
(command "_circle" "639.0625,-39.0693" "0.075")
(command "_circle" "638.7625,-40.2693" "0.075")
(command "_circle" "638.7625,-39.9693" "0.075")
(command "_circle" "638.7625,-39.6693" "0.075")
(command "_circle" "638.7625,-39.3693" "0.075")
(command "_circle" "638.7625,-39.0693" "0.075")
(command "_circle" "638.4625,-40.2693" "0.075")
(command "_circle" "638.4625,-39.9693" "0.075")
(command "_circle" "638.4625,-39.6693" "0.075")
(command "_circle" "638.4625,-39.3693" "0.075")
(command "_circle" "638.4625,-39.0693" "0.075")
(command "_circle" "638.1625,-40.2693" "0.075")
(command "_circle" "638.1625,-39.9693" "0.075")
(command "_circle" "638.1625,-39.6693" "0.075")
(command "_circle" "638.1625,-39.3693" "0.075")
(command "_circle" "638.1625,-39.0693" "0.075")
(command "_circle" "637.8625,-40.2693" "0.075")
(command "_circle" "637.8625,-39.9693" "0.075")
(command "_circle" "637.8625,-39.6693" "0.075")
(command "_circle" "637.8625,-39.3693" "0.075")
(command "_circle" "637.8625,-39.0693" "0.075")
(command "_layer" "set" "nitride" "")
(setq coords (list 
(list 640.2625 -14.8263) 
(list 640.2625 100.8184) 
(list 639.7375 100.8184) 
(list 639.7375 -14.8263)))
(apply 'command (append '("pline") coords '("c")))
(setq currobj (ssadd (entlast) currobj))
(command "_layer" "set" "prebias" "")
(command "_rectangle" "639.7375,-14.8263" "640.2625,100.8184")
(setq currobj (ssadd (entlast) currobj))
(command "_layer" "set" "nitride" "")
(setq coords (list 
(list 640.2625 100.8184) 
(list 640.5625 110.8184) 
(list 640.5625 110.8184) 
(list 640.5625 111.8184) 
(list 714.585 111.0684) 
(list 714.585 116.0114) 
(list 640.5625 115.2614) 
(list 640.5625 116.2614) 
(list 640.5625 116.2614) 
(list 640.2625 126.2614) 
(list 639.7375 126.2614) 
(list 639.4375 116.2614) 
(list 639.4375 116.2614) 
(list 639.4375 115.2614) 
(list 565.415 116.0114) 
(list 565.415 111.0684) 
(list 639.4375 111.8184) 
(list 639.4375 110.8184) 
(list 639.4375 110.8184) 
(list 639.7375 100.8184)))
(apply 'command (append '("pline") coords '("c")))
(setq currobj (ssadd (entlast) currobj))
(command "_layer" "set" "prebias" "")
(setq coords (list 
(list 639.4375 100.8184) 
(list 639.4375 111.8184) 
(list 565.415 111.0684) 
(list 565.415 116.0114) 
(list 639.4375 115.2614) 
(list 639.4375 126.2614) 
(list 640.5625 126.2614) 
(list 640.5625 115.2614) 
(list 714.585 116.0114) 
(list 714.585 111.0684) 
(list 640.5625 111.8184) 
(list 640.5625 100.8184)))
(apply 'command (append '("pline") coords '("c")))
(setq currobj (ssadd (entlast) currobj))
(command "_layer" "set" "nitride" "")
(command "_layer" "set" "fda1" "")
(setq coords (list 
(list 640.5625 111.9614) 
(list 714.585 111.2114) 
(list 714.585 111.3884) 
(list 640.5625 112.0384)))
(apply 'command (append '("pline") coords '("c")))
(setq currobj (ssadd (entlast) currobj))
(setq coords (list 
(list 640.5625 112.1814) 
(list 714.585 111.5314) 
(list 714.585 111.7084) 
(list 640.5625 112.2584)))
(apply 'command (append '("pline") coords '("c")))
(setq currobj (ssadd (entlast) currobj))
(setq coords (list 
(list 640.5625 112.4014) 
(list 714.585 111.8514) 
(list 714.585 112.0284) 
(list 640.5625 112.4784)))
(apply 'command (append '("pline") coords '("c")))
(setq currobj (ssadd (entlast) currobj))
(setq coords (list 
(list 640.5625 112.6214) 
(list 714.585 112.1714) 
(list 714.585 112.3484) 
(list 640.5625 112.6984)))
(apply 'command (append '("pline") coords '("c")))
(setq currobj (ssadd (entlast) currobj))
(setq coords (list 
(list 640.5625 112.8414) 
(list 714.585 112.4914) 
(list 714.585 112.6684) 
(list 640.5625 112.9184)))
(apply 'command (append '("pline") coords '("c")))
(setq currobj (ssadd (entlast) currobj))
(setq coords (list 
(list 640.5625 113.0614) 
(list 714.585 112.8114) 
(list 714.585 112.9884) 
(list 640.5625 113.1384)))
(apply 'command (append '("pline") coords '("c")))
(setq currobj (ssadd (entlast) currobj))
(setq coords (list 
(list 640.5625 113.2814) 
(list 714.585 113.1314) 
(list 714.585 113.3084) 
(list 640.5625 113.3584)))
(apply 'command (append '("pline") coords '("c")))
(setq currobj (ssadd (entlast) currobj))
(setq coords (list 
(list 640.5625 113.5014) 
(list 714.585 113.4514) 
(list 714.585 113.6284) 
(list 640.5625 113.5784)))
(apply 'command (append '("pline") coords '("c")))
(setq currobj (ssadd (entlast) currobj))
(setq coords (list 
(list 640.5625 113.7214) 
(list 714.585 113.7714) 
(list 714.585 113.9484) 
(list 640.5625 113.7984)))
(apply 'command (append '("pline") coords '("c")))
(setq currobj (ssadd (entlast) currobj))
(setq coords (list 
(list 640.5625 113.9414) 
(list 714.585 114.0914) 
(list 714.585 114.2684) 
(list 640.5625 114.0184)))
(apply 'command (append '("pline") coords '("c")))
(setq currobj (ssadd (entlast) currobj))
(setq coords (list 
(list 640.5625 114.1614) 
(list 714.585 114.4114) 
(list 714.585 114.5884) 
(list 640.5625 114.2384)))
(apply 'command (append '("pline") coords '("c")))
(setq currobj (ssadd (entlast) currobj))
(setq coords (list 
(list 640.5625 114.3814) 
(list 714.585 114.7314) 
(list 714.585 114.9084) 
(list 640.5625 114.4584)))
(apply 'command (append '("pline") coords '("c")))
(setq currobj (ssadd (entlast) currobj))
(setq coords (list 
(list 640.5625 114.6014) 
(list 714.585 115.0514) 
(list 714.585 115.2284) 
(list 640.5625 114.6784)))
(apply 'command (append '("pline") coords '("c")))
(setq currobj (ssadd (entlast) currobj))
(setq coords (list 
(list 640.5625 114.8214) 
(list 714.585 115.3714) 
(list 714.585 115.5484) 
(list 640.5625 114.8984)))
(apply 'command (append '("pline") coords '("c")))
(setq currobj (ssadd (entlast) currobj))
(setq coords (list 
(list 640.5625 115.0414) 
(list 714.585 115.6914) 
(list 714.585 115.8684) 
(list 640.5625 115.1184)))
(apply 'command (append '("pline") coords '("c")))
(setq currobj (ssadd (entlast) currobj))
(setq coords (list 
(list 639.4375 115.1184) 
(list 565.415 115.8684) 
(list 565.415 115.6914) 
(list 639.4375 115.0414)))
(apply 'command (append '("pline") coords '("c")))
(setq currobj (ssadd (entlast) currobj))
(setq coords (list 
(list 639.4375 114.8984) 
(list 565.415 115.5484) 
(list 565.415 115.3714) 
(list 639.4375 114.8214)))
(apply 'command (append '("pline") coords '("c")))
(setq currobj (ssadd (entlast) currobj))
(setq coords (list 
(list 639.4375 114.6784) 
(list 565.415 115.2284) 
(list 565.415 115.0514) 
(list 639.4375 114.6014)))
(apply 'command (append '("pline") coords '("c")))
(setq currobj (ssadd (entlast) currobj))
(setq coords (list 
(list 639.4375 114.4584) 
(list 565.415 114.9084) 
(list 565.415 114.7314) 
(list 639.4375 114.3814)))
(apply 'command (append '("pline") coords '("c")))
(setq currobj (ssadd (entlast) currobj))
(setq coords (list 
(list 639.4375 114.2384) 
(list 565.415 114.5884) 
(list 565.415 114.4114) 
(list 639.4375 114.1614)))
(apply 'command (append '("pline") coords '("c")))
(setq currobj (ssadd (entlast) currobj))
(setq coords (list 
(list 639.4375 114.0184) 
(list 565.415 114.2684) 
(list 565.415 114.0914) 
(list 639.4375 113.9414)))
(apply 'command (append '("pline") coords '("c")))
(setq currobj (ssadd (entlast) currobj))
(setq coords (list 
(list 639.4375 113.7984) 
(list 565.415 113.9484) 
(list 565.415 113.7714) 
(list 639.4375 113.7214)))
(apply 'command (append '("pline") coords '("c")))
(setq currobj (ssadd (entlast) currobj))
(setq coords (list 
(list 639.4375 113.5784) 
(list 565.415 113.6284) 
(list 565.415 113.4514) 
(list 639.4375 113.5014)))
(apply 'command (append '("pline") coords '("c")))
(setq currobj (ssadd (entlast) currobj))
(setq coords (list 
(list 639.4375 113.3584) 
(list 565.415 113.3084) 
(list 565.415 113.1314) 
(list 639.4375 113.2814)))
(apply 'command (append '("pline") coords '("c")))
(setq currobj (ssadd (entlast) currobj))
(setq coords (list 
(list 639.4375 113.1384) 
(list 565.415 112.9884) 
(list 565.415 112.8114) 
(list 639.4375 113.0614)))
(apply 'command (append '("pline") coords '("c")))
(setq currobj (ssadd (entlast) currobj))
(setq coords (list 
(list 639.4375 112.9184) 
(list 565.415 112.6684) 
(list 565.415 112.4914) 
(list 639.4375 112.8414)))
(apply 'command (append '("pline") coords '("c")))
(setq currobj (ssadd (entlast) currobj))
(setq coords (list 
(list 639.4375 112.6984) 
(list 565.415 112.3484) 
(list 565.415 112.1714) 
(list 639.4375 112.6214)))
(apply 'command (append '("pline") coords '("c")))
(setq currobj (ssadd (entlast) currobj))
(setq coords (list 
(list 639.4375 112.4784) 
(list 565.415 112.0284) 
(list 565.415 111.8514) 
(list 639.4375 112.4014)))
(apply 'command (append '("pline") coords '("c")))
(setq currobj (ssadd (entlast) currobj))
(setq coords (list 
(list 639.4375 112.2584) 
(list 565.415 111.7084) 
(list 565.415 111.5314) 
(list 639.4375 112.1814)))
(apply 'command (append '("pline") coords '("c")))
(setq currobj (ssadd (entlast) currobj))
(setq coords (list 
(list 639.4375 112.0384) 
(list 565.415 111.3884) 
(list 565.415 111.2114) 
(list 639.4375 111.9614)))
(apply 'command (append '("pline") coords '("c")))
(setq currobj (ssadd (entlast) currobj))
(command "_layer" "set" "nitride" "")
(command "_layer" "set" "text" "")
(command "_circle" "639.0625,100.8184" "0.075")
(command "_circle" "639.0625,101.1184" "0.075")
(command "_circle" "639.0625,101.4184" "0.075")
(command "_circle" "639.0625,101.7184" "0.075")
(command "_circle" "639.0625,102.0184" "0.075")
(command "_circle" "638.7625,100.8184" "0.075")
(command "_circle" "638.7625,101.1184" "0.075")
(command "_circle" "638.7625,101.4184" "0.075")
(command "_circle" "638.7625,101.7184" "0.075")
(command "_circle" "638.7625,102.0184" "0.075")
(command "_circle" "638.4625,100.8184" "0.075")
(command "_circle" "638.4625,101.1184" "0.075")
(command "_circle" "638.4625,101.4184" "0.075")
(command "_circle" "638.4625,101.7184" "0.075")
(command "_circle" "638.4625,102.0184" "0.075")
(command "_circle" "638.1625,100.8184" "0.075")
(command "_circle" "638.1625,101.1184" "0.075")
(command "_circle" "638.1625,101.4184" "0.075")
(command "_circle" "638.1625,101.7184" "0.075")
(command "_circle" "638.1625,102.0184" "0.075")
(command "_circle" "637.8625,100.8184" "0.075")
(command "_circle" "637.8625,101.1184" "0.075")
(command "_circle" "637.8625,101.4184" "0.075")
(command "_circle" "637.8625,101.7184" "0.075")
(command "_circle" "637.8625,102.0184" "0.075")
(command "_layer" "set" "nitride" "")
(setq coords (list 
(list 640.2625 126.2614) 
(list 640.2625 241.9061) 
(list 639.7375 241.9061) 
(list 639.7375 126.2614)))
(apply 'command (append '("pline") coords '("c")))
(setq currobj (ssadd (entlast) currobj))
(command "_layer" "set" "prebias" "")
(command "_rectangle" "639.7375,126.2614" "640.2625,241.9061")
(setq currobj (ssadd (entlast) currobj))
(command "_layer" "set" "nitride" "")
(setq coords (list 
(list 640.2625 241.9061) 
(list 640.5625 251.9061) 
(list 640.5625 251.9061) 
(list 640.5625 252.9061) 
(list 714.585 252.1561) 
(list 714.585 257.0991) 
(list 640.5625 256.3491) 
(list 640.5625 257.3491) 
(list 640.5625 257.3491) 
(list 640.2625 267.3491) 
(list 639.7375 267.3491) 
(list 639.4375 257.3491) 
(list 639.4375 257.3491) 
(list 639.4375 256.3491) 
(list 565.415 257.0991) 
(list 565.415 252.1561) 
(list 639.4375 252.9061) 
(list 639.4375 251.9061) 
(list 639.4375 251.9061) 
(list 639.7375 241.9061)))
(apply 'command (append '("pline") coords '("c")))
(setq currobj (ssadd (entlast) currobj))
(command "_layer" "set" "prebias" "")
(setq coords (list 
(list 639.4375 241.9061) 
(list 639.4375 252.9061) 
(list 565.415 252.1561) 
(list 565.415 257.0991) 
(list 639.4375 256.3491) 
(list 639.4375 267.3491) 
(list 640.5625 267.3491) 
(list 640.5625 256.3491) 
(list 714.585 257.0991) 
(list 714.585 252.1561) 
(list 640.5625 252.9061) 
(list 640.5625 241.9061)))
(apply 'command (append '("pline") coords '("c")))
(setq currobj (ssadd (entlast) currobj))
(command "_layer" "set" "nitride" "")
(command "_layer" "set" "fda1" "")
(setq coords (list 
(list 640.5625 253.0491) 
(list 714.585 252.2991) 
(list 714.585 252.4761) 
(list 640.5625 253.1261)))
(apply 'command (append '("pline") coords '("c")))
(setq currobj (ssadd (entlast) currobj))
(setq coords (list 
(list 640.5625 253.2691) 
(list 714.585 252.6191) 
(list 714.585 252.7961) 
(list 640.5625 253.3461)))
(apply 'command (append '("pline") coords '("c")))
(setq currobj (ssadd (entlast) currobj))
(setq coords (list 
(list 640.5625 253.4891) 
(list 714.585 252.9391) 
(list 714.585 253.1161) 
(list 640.5625 253.5661)))
(apply 'command (append '("pline") coords '("c")))
(setq currobj (ssadd (entlast) currobj))
(setq coords (list 
(list 640.5625 253.7091) 
(list 714.585 253.2591) 
(list 714.585 253.4361) 
(list 640.5625 253.7861)))
(apply 'command (append '("pline") coords '("c")))
(setq currobj (ssadd (entlast) currobj))
(setq coords (list 
(list 640.5625 253.9291) 
(list 714.585 253.5791) 
(list 714.585 253.7561) 
(list 640.5625 254.0061)))
(apply 'command (append '("pline") coords '("c")))
(setq currobj (ssadd (entlast) currobj))
(setq coords (list 
(list 640.5625 254.1491) 
(list 714.585 253.8991) 
(list 714.585 254.0761) 
(list 640.5625 254.2261)))
(apply 'command (append '("pline") coords '("c")))
(setq currobj (ssadd (entlast) currobj))
(setq coords (list 
(list 640.5625 254.3691) 
(list 714.585 254.2191) 
(list 714.585 254.3961) 
(list 640.5625 254.4461)))
(apply 'command (append '("pline") coords '("c")))
(setq currobj (ssadd (entlast) currobj))
(setq coords (list 
(list 640.5625 254.5891) 
(list 714.585 254.5391) 
(list 714.585 254.7161) 
(list 640.5625 254.6661)))
(apply 'command (append '("pline") coords '("c")))
(setq currobj (ssadd (entlast) currobj))
(setq coords (list 
(list 640.5625 254.8091) 
(list 714.585 254.8591) 
(list 714.585 255.0361) 
(list 640.5625 254.8861)))
(apply 'command (append '("pline") coords '("c")))
(setq currobj (ssadd (entlast) currobj))
(setq coords (list 
(list 640.5625 255.0291) 
(list 714.585 255.1791) 
(list 714.585 255.3561) 
(list 640.5625 255.1061)))
(apply 'command (append '("pline") coords '("c")))
(setq currobj (ssadd (entlast) currobj))
(setq coords (list 
(list 640.5625 255.2491) 
(list 714.585 255.4991) 
(list 714.585 255.6761) 
(list 640.5625 255.3261)))
(apply 'command (append '("pline") coords '("c")))
(setq currobj (ssadd (entlast) currobj))
(setq coords (list 
(list 640.5625 255.4691) 
(list 714.585 255.8191) 
(list 714.585 255.9961) 
(list 640.5625 255.5461)))
(apply 'command (append '("pline") coords '("c")))
(setq currobj (ssadd (entlast) currobj))
(setq coords (list 
(list 640.5625 255.6891) 
(list 714.585 256.1391) 
(list 714.585 256.3161) 
(list 640.5625 255.7661)))
(apply 'command (append '("pline") coords '("c")))
(setq currobj (ssadd (entlast) currobj))
(setq coords (list 
(list 640.5625 255.9091) 
(list 714.585 256.4591) 
(list 714.585 256.6361) 
(list 640.5625 255.9861)))
(apply 'command (append '("pline") coords '("c")))
(setq currobj (ssadd (entlast) currobj))
(setq coords (list 
(list 640.5625 256.1291) 
(list 714.585 256.7791) 
(list 714.585 256.9561) 
(list 640.5625 256.2061)))
(apply 'command (append '("pline") coords '("c")))
(setq currobj (ssadd (entlast) currobj))
(setq coords (list 
(list 639.4375 256.2061) 
(list 565.415 256.9561) 
(list 565.415 256.7791) 
(list 639.4375 256.1291)))
(apply 'command (append '("pline") coords '("c")))
(setq currobj (ssadd (entlast) currobj))
(setq coords (list 
(list 639.4375 255.9861) 
(list 565.415 256.6361) 
(list 565.415 256.4591) 
(list 639.4375 255.9091)))
(apply 'command (append '("pline") coords '("c")))
(setq currobj (ssadd (entlast) currobj))
(setq coords (list 
(list 639.4375 255.7661) 
(list 565.415 256.3161) 
(list 565.415 256.1391) 
(list 639.4375 255.6891)))
(apply 'command (append '("pline") coords '("c")))
(setq currobj (ssadd (entlast) currobj))
(setq coords (list 
(list 639.4375 255.5461) 
(list 565.415 255.9961) 
(list 565.415 255.8191) 
(list 639.4375 255.4691)))
(apply 'command (append '("pline") coords '("c")))
(setq currobj (ssadd (entlast) currobj))
(setq coords (list 
(list 639.4375 255.3261) 
(list 565.415 255.6761) 
(list 565.415 255.4991) 
(list 639.4375 255.2491)))
(apply 'command (append '("pline") coords '("c")))
(setq currobj (ssadd (entlast) currobj))
(setq coords (list 
(list 639.4375 255.1061) 
(list 565.415 255.3561) 
(list 565.415 255.1791) 
(list 639.4375 255.0291)))
(apply 'command (append '("pline") coords '("c")))
(setq currobj (ssadd (entlast) currobj))
(setq coords (list 
(list 639.4375 254.8861) 
(list 565.415 255.0361) 
(list 565.415 254.8591) 
(list 639.4375 254.8091)))
(apply 'command (append '("pline") coords '("c")))
(setq currobj (ssadd (entlast) currobj))
(setq coords (list 
(list 639.4375 254.6661) 
(list 565.415 254.7161) 
(list 565.415 254.5391) 
(list 639.4375 254.5891)))
(apply 'command (append '("pline") coords '("c")))
(setq currobj (ssadd (entlast) currobj))
(setq coords (list 
(list 639.4375 254.4461) 
(list 565.415 254.3961) 
(list 565.415 254.2191) 
(list 639.4375 254.3691)))
(apply 'command (append '("pline") coords '("c")))
(setq currobj (ssadd (entlast) currobj))
(setq coords (list 
(list 639.4375 254.2261) 
(list 565.415 254.0761) 
(list 565.415 253.8991) 
(list 639.4375 254.1491)))
(apply 'command (append '("pline") coords '("c")))
(setq currobj (ssadd (entlast) currobj))
(setq coords (list 
(list 639.4375 254.0061) 
(list 565.415 253.7561) 
(list 565.415 253.5791) 
(list 639.4375 253.9291)))
(apply 'command (append '("pline") coords '("c")))
(setq currobj (ssadd (entlast) currobj))
(setq coords (list 
(list 639.4375 253.7861) 
(list 565.415 253.4361) 
(list 565.415 253.2591) 
(list 639.4375 253.7091)))
(apply 'command (append '("pline") coords '("c")))
(setq currobj (ssadd (entlast) currobj))
(setq coords (list 
(list 639.4375 253.5661) 
(list 565.415 253.1161) 
(list 565.415 252.9391) 
(list 639.4375 253.4891)))
(apply 'command (append '("pline") coords '("c")))
(setq currobj (ssadd (entlast) currobj))
(setq coords (list 
(list 639.4375 253.3461) 
(list 565.415 252.7961) 
(list 565.415 252.6191) 
(list 639.4375 253.2691)))
(apply 'command (append '("pline") coords '("c")))
(setq currobj (ssadd (entlast) currobj))
(setq coords (list 
(list 639.4375 253.1261) 
(list 565.415 252.4761) 
(list 565.415 252.2991) 
(list 639.4375 253.0491)))
(apply 'command (append '("pline") coords '("c")))
(setq currobj (ssadd (entlast) currobj))
(command "_layer" "set" "nitride" "")
(command "_layer" "set" "text" "")
(command "_circle" "639.0625,241.9061" "0.075")
(command "_circle" "639.0625,242.2061" "0.075")
(command "_circle" "639.0625,242.5061" "0.075")
(command "_circle" "639.0625,242.8061" "0.075")
(command "_circle" "639.0625,243.1061" "0.075")
(command "_circle" "638.7625,241.9061" "0.075")
(command "_circle" "638.7625,242.2061" "0.075")
(command "_circle" "638.7625,242.5061" "0.075")
(command "_circle" "638.7625,242.8061" "0.075")
(command "_circle" "638.7625,243.1061" "0.075")
(command "_circle" "638.4625,241.9061" "0.075")
(command "_circle" "638.4625,242.2061" "0.075")
(command "_circle" "638.4625,242.5061" "0.075")
(command "_circle" "638.4625,242.8061" "0.075")
(command "_circle" "638.4625,243.1061" "0.075")
(command "_circle" "638.1625,241.9061" "0.075")
(command "_circle" "638.1625,242.2061" "0.075")
(command "_circle" "638.1625,242.5061" "0.075")
(command "_circle" "638.1625,242.8061" "0.075")
(command "_circle" "638.1625,243.1061" "0.075")
(command "_circle" "637.8625,241.9061" "0.075")
(command "_circle" "637.8625,242.2061" "0.075")
(command "_circle" "637.8625,242.5061" "0.075")
(command "_circle" "637.8625,242.8061" "0.075")
(command "_circle" "637.8625,243.1061" "0.075")
(command "_layer" "set" "nitride" "")
(setq coords (list 
(list 640.2625 267.3491) 
(list 640.2625 382.9939) 
(list 639.7375 382.9939) 
(list 639.7375 267.3491)))
(apply 'command (append '("pline") coords '("c")))
(setq currobj (ssadd (entlast) currobj))
(command "_layer" "set" "prebias" "")
(command "_rectangle" "639.7375,267.3491" "640.2625,382.9939")
(setq currobj (ssadd (entlast) currobj))
(command "_layer" "set" "nitride" "")
(setq coords (list 
(list 640.2625 382.9939) 
(list 640.5625 392.9939) 
(list 640.5625 392.9939) 
(list 640.5625 393.9939) 
(list 714.585 393.2439) 
(list 714.585 398.1869) 
(list 640.5625 397.4369) 
(list 640.5625 398.4369) 
(list 640.5625 398.4369) 
(list 640.2625 408.4369) 
(list 639.7375 408.4369) 
(list 639.4375 398.4369) 
(list 639.4375 398.4369) 
(list 639.4375 397.4369) 
(list 565.415 398.1869) 
(list 565.415 393.2439) 
(list 639.4375 393.9939) 
(list 639.4375 392.9939) 
(list 639.4375 392.9939) 
(list 639.7375 382.9939)))
(apply 'command (append '("pline") coords '("c")))
(setq currobj (ssadd (entlast) currobj))
(command "_layer" "set" "prebias" "")
(setq coords (list 
(list 639.4375 382.9939) 
(list 639.4375 393.9939) 
(list 565.415 393.2439) 
(list 565.415 398.1869) 
(list 639.4375 397.4369) 
(list 639.4375 408.4369) 
(list 640.5625 408.4369) 
(list 640.5625 397.4369) 
(list 714.585 398.1869) 
(list 714.585 393.2439) 
(list 640.5625 393.9939) 
(list 640.5625 382.9939)))
(apply 'command (append '("pline") coords '("c")))
(setq currobj (ssadd (entlast) currobj))
(command "_layer" "set" "nitride" "")
(command "_layer" "set" "fda1" "")
(setq coords (list 
(list 640.5625 394.1369) 
(list 714.585 393.3869) 
(list 714.585 393.5639) 
(list 640.5625 394.2139)))
(apply 'command (append '("pline") coords '("c")))
(setq currobj (ssadd (entlast) currobj))
(setq coords (list 
(list 640.5625 394.3569) 
(list 714.585 393.7069) 
(list 714.585 393.8839) 
(list 640.5625 394.4339)))
(apply 'command (append '("pline") coords '("c")))
(setq currobj (ssadd (entlast) currobj))
(setq coords (list 
(list 640.5625 394.5769) 
(list 714.585 394.0269) 
(list 714.585 394.2039) 
(list 640.5625 394.6539)))
(apply 'command (append '("pline") coords '("c")))
(setq currobj (ssadd (entlast) currobj))
(setq coords (list 
(list 640.5625 394.7969) 
(list 714.585 394.3469) 
(list 714.585 394.5239) 
(list 640.5625 394.8739)))
(apply 'command (append '("pline") coords '("c")))
(setq currobj (ssadd (entlast) currobj))
(setq coords (list 
(list 640.5625 395.0169) 
(list 714.585 394.6669) 
(list 714.585 394.8439) 
(list 640.5625 395.0939)))
(apply 'command (append '("pline") coords '("c")))
(setq currobj (ssadd (entlast) currobj))
(setq coords (list 
(list 640.5625 395.2369) 
(list 714.585 394.9869) 
(list 714.585 395.1639) 
(list 640.5625 395.3139)))
(apply 'command (append '("pline") coords '("c")))
(setq currobj (ssadd (entlast) currobj))
(setq coords (list 
(list 640.5625 395.4569) 
(list 714.585 395.3069) 
(list 714.585 395.4839) 
(list 640.5625 395.5339)))
(apply 'command (append '("pline") coords '("c")))
(setq currobj (ssadd (entlast) currobj))
(setq coords (list 
(list 640.5625 395.6769) 
(list 714.585 395.6269) 
(list 714.585 395.8039) 
(list 640.5625 395.7539)))
(apply 'command (append '("pline") coords '("c")))
(setq currobj (ssadd (entlast) currobj))
(setq coords (list 
(list 640.5625 395.8969) 
(list 714.585 395.9469) 
(list 714.585 396.1239) 
(list 640.5625 395.9739)))
(apply 'command (append '("pline") coords '("c")))
(setq currobj (ssadd (entlast) currobj))
(setq coords (list 
(list 640.5625 396.1169) 
(list 714.585 396.2669) 
(list 714.585 396.4439) 
(list 640.5625 396.1939)))
(apply 'command (append '("pline") coords '("c")))
(setq currobj (ssadd (entlast) currobj))
(setq coords (list 
(list 640.5625 396.3369) 
(list 714.585 396.5869) 
(list 714.585 396.7639) 
(list 640.5625 396.4139)))
(apply 'command (append '("pline") coords '("c")))
(setq currobj (ssadd (entlast) currobj))
(setq coords (list 
(list 640.5625 396.5569) 
(list 714.585 396.9069) 
(list 714.585 397.0839) 
(list 640.5625 396.6339)))
(apply 'command (append '("pline") coords '("c")))
(setq currobj (ssadd (entlast) currobj))
(setq coords (list 
(list 640.5625 396.7769) 
(list 714.585 397.2269) 
(list 714.585 397.4039) 
(list 640.5625 396.8539)))
(apply 'command (append '("pline") coords '("c")))
(setq currobj (ssadd (entlast) currobj))
(setq coords (list 
(list 640.5625 396.9969) 
(list 714.585 397.5469) 
(list 714.585 397.7239) 
(list 640.5625 397.0739)))
(apply 'command (append '("pline") coords '("c")))
(setq currobj (ssadd (entlast) currobj))
(setq coords (list 
(list 640.5625 397.2169) 
(list 714.585 397.8669) 
(list 714.585 398.0439) 
(list 640.5625 397.2939)))
(apply 'command (append '("pline") coords '("c")))
(setq currobj (ssadd (entlast) currobj))
(setq coords (list 
(list 639.4375 397.2939) 
(list 565.415 398.0439) 
(list 565.415 397.8669) 
(list 639.4375 397.2169)))
(apply 'command (append '("pline") coords '("c")))
(setq currobj (ssadd (entlast) currobj))
(setq coords (list 
(list 639.4375 397.0739) 
(list 565.415 397.7239) 
(list 565.415 397.5469) 
(list 639.4375 396.9969)))
(apply 'command (append '("pline") coords '("c")))
(setq currobj (ssadd (entlast) currobj))
(setq coords (list 
(list 639.4375 396.8539) 
(list 565.415 397.4039) 
(list 565.415 397.2269) 
(list 639.4375 396.7769)))
(apply 'command (append '("pline") coords '("c")))
(setq currobj (ssadd (entlast) currobj))
(setq coords (list 
(list 639.4375 396.6339) 
(list 565.415 397.0839) 
(list 565.415 396.9069) 
(list 639.4375 396.5569)))
(apply 'command (append '("pline") coords '("c")))
(setq currobj (ssadd (entlast) currobj))
(setq coords (list 
(list 639.4375 396.4139) 
(list 565.415 396.7639) 
(list 565.415 396.5869) 
(list 639.4375 396.3369)))
(apply 'command (append '("pline") coords '("c")))
(setq currobj (ssadd (entlast) currobj))
(setq coords (list 
(list 639.4375 396.1939) 
(list 565.415 396.4439) 
(list 565.415 396.2669) 
(list 639.4375 396.1169)))
(apply 'command (append '("pline") coords '("c")))
(setq currobj (ssadd (entlast) currobj))
(setq coords (list 
(list 639.4375 395.9739) 
(list 565.415 396.1239) 
(list 565.415 395.9469) 
(list 639.4375 395.8969)))
(apply 'command (append '("pline") coords '("c")))
(setq currobj (ssadd (entlast) currobj))
(setq coords (list 
(list 639.4375 395.7539) 
(list 565.415 395.8039) 
(list 565.415 395.6269) 
(list 639.4375 395.6769)))
(apply 'command (append '("pline") coords '("c")))
(setq currobj (ssadd (entlast) currobj))
(setq coords (list 
(list 639.4375 395.5339) 
(list 565.415 395.4839) 
(list 565.415 395.3069) 
(list 639.4375 395.4569)))
(apply 'command (append '("pline") coords '("c")))
(setq currobj (ssadd (entlast) currobj))
(setq coords (list 
(list 639.4375 395.3139) 
(list 565.415 395.1639) 
(list 565.415 394.9869) 
(list 639.4375 395.2369)))
(apply 'command (append '("pline") coords '("c")))
(setq currobj (ssadd (entlast) currobj))
(setq coords (list 
(list 639.4375 395.0939) 
(list 565.415 394.8439) 
(list 565.415 394.6669) 
(list 639.4375 395.0169)))
(apply 'command (append '("pline") coords '("c")))
(setq currobj (ssadd (entlast) currobj))
(setq coords (list 
(list 639.4375 394.8739) 
(list 565.415 394.5239) 
(list 565.415 394.3469) 
(list 639.4375 394.7969)))
(apply 'command (append '("pline") coords '("c")))
(setq currobj (ssadd (entlast) currobj))
(setq coords (list 
(list 639.4375 394.6539) 
(list 565.415 394.2039) 
(list 565.415 394.0269) 
(list 639.4375 394.5769)))
(apply 'command (append '("pline") coords '("c")))
(setq currobj (ssadd (entlast) currobj))
(setq coords (list 
(list 639.4375 394.4339) 
(list 565.415 393.8839) 
(list 565.415 393.7069) 
(list 639.4375 394.3569)))
(apply 'command (append '("pline") coords '("c")))
(setq currobj (ssadd (entlast) currobj))
(setq coords (list 
(list 639.4375 394.2139) 
(list 565.415 393.5639) 
(list 565.415 393.3869) 
(list 639.4375 394.1369)))
(apply 'command (append '("pline") coords '("c")))
(setq currobj (ssadd (entlast) currobj))
(command "_layer" "set" "nitride" "")
(command "_layer" "set" "text" "")
(command "_circle" "639.0625,382.9939" "0.075")
(command "_circle" "639.0625,383.2939" "0.075")
(command "_circle" "639.0625,383.5939" "0.075")
(command "_circle" "639.0625,383.8939" "0.075")
(command "_circle" "639.0625,384.1939" "0.075")
(command "_circle" "638.7625,382.9939" "0.075")
(command "_circle" "638.7625,383.2939" "0.075")
(command "_circle" "638.7625,383.5939" "0.075")
(command "_circle" "638.7625,383.8939" "0.075")
(command "_circle" "638.7625,384.1939" "0.075")
(command "_circle" "638.4625,382.9939" "0.075")
(command "_circle" "638.4625,383.2939" "0.075")
(command "_circle" "638.4625,383.5939" "0.075")
(command "_circle" "638.4625,383.8939" "0.075")
(command "_circle" "638.4625,384.1939" "0.075")
(command "_circle" "638.1625,382.9939" "0.075")
(command "_circle" "638.1625,383.2939" "0.075")
(command "_circle" "638.1625,383.5939" "0.075")
(command "_circle" "638.1625,383.8939" "0.075")
(command "_circle" "638.1625,384.1939" "0.075")
(command "_circle" "637.8625,382.9939" "0.075")
(command "_circle" "637.8625,383.2939" "0.075")
(command "_circle" "637.8625,383.5939" "0.075")
(command "_circle" "637.8625,383.8939" "0.075")
(command "_circle" "637.8625,384.1939" "0.075")
(command "_layer" "set" "nitride" "")
(setq coords (list 
(list 640.2625 408.4369) 
(list 640.2625 524.0816) 
(list 639.7375 524.0816) 
(list 639.7375 408.4369)))
(apply 'command (append '("pline") coords '("c")))
(setq currobj (ssadd (entlast) currobj))
(command "_layer" "set" "prebias" "")
(command "_rectangle" "639.7375,408.4369" "640.2625,524.0816")
(setq currobj (ssadd (entlast) currobj))
(command "_layer" "set" "nitride" "")
(setq coords (list 
(list 640.2625 524.0816) 
(list 640.5625 534.0816) 
(list 640.5625 534.0816) 
(list 640.5625 535.0816) 
(list 714.585 534.3316) 
(list 714.585 539.2746) 
(list 640.5625 538.5246) 
(list 640.5625 539.5246) 
(list 640.5625 539.5246) 
(list 640.2625 549.5246) 
(list 639.7375 549.5246) 
(list 639.4375 539.5246) 
(list 639.4375 539.5246) 
(list 639.4375 538.5246) 
(list 565.415 539.2746) 
(list 565.415 534.3316) 
(list 639.4375 535.0816) 
(list 639.4375 534.0816) 
(list 639.4375 534.0816) 
(list 639.7375 524.0816)))
(apply 'command (append '("pline") coords '("c")))
(setq currobj (ssadd (entlast) currobj))
(command "_layer" "set" "prebias" "")
(setq coords (list 
(list 639.4375 524.0816) 
(list 639.4375 535.0816) 
(list 565.415 534.3316) 
(list 565.415 539.2746) 
(list 639.4375 538.5246) 
(list 639.4375 549.5246) 
(list 640.5625 549.5246) 
(list 640.5625 538.5246) 
(list 714.585 539.2746) 
(list 714.585 534.3316) 
(list 640.5625 535.0816) 
(list 640.5625 524.0816)))
(apply 'command (append '("pline") coords '("c")))
(setq currobj (ssadd (entlast) currobj))
(command "_layer" "set" "nitride" "")
(command "_layer" "set" "fda1" "")
(setq coords (list 
(list 640.5625 535.2246) 
(list 714.585 534.4746) 
(list 714.585 534.6516) 
(list 640.5625 535.3016)))
(apply 'command (append '("pline") coords '("c")))
(setq currobj (ssadd (entlast) currobj))
(setq coords (list 
(list 640.5625 535.4446) 
(list 714.585 534.7946) 
(list 714.585 534.9716) 
(list 640.5625 535.5216)))
(apply 'command (append '("pline") coords '("c")))
(setq currobj (ssadd (entlast) currobj))
(setq coords (list 
(list 640.5625 535.6646) 
(list 714.585 535.1146) 
(list 714.585 535.2916) 
(list 640.5625 535.7416)))
(apply 'command (append '("pline") coords '("c")))
(setq currobj (ssadd (entlast) currobj))
(setq coords (list 
(list 640.5625 535.8846) 
(list 714.585 535.4346) 
(list 714.585 535.6116) 
(list 640.5625 535.9616)))
(apply 'command (append '("pline") coords '("c")))
(setq currobj (ssadd (entlast) currobj))
(setq coords (list 
(list 640.5625 536.1046) 
(list 714.585 535.7546) 
(list 714.585 535.9316) 
(list 640.5625 536.1816)))
(apply 'command (append '("pline") coords '("c")))
(setq currobj (ssadd (entlast) currobj))
(setq coords (list 
(list 640.5625 536.3246) 
(list 714.585 536.0746) 
(list 714.585 536.2516) 
(list 640.5625 536.4016)))
(apply 'command (append '("pline") coords '("c")))
(setq currobj (ssadd (entlast) currobj))
(setq coords (list 
(list 640.5625 536.5446) 
(list 714.585 536.3946) 
(list 714.585 536.5716) 
(list 640.5625 536.6216)))
(apply 'command (append '("pline") coords '("c")))
(setq currobj (ssadd (entlast) currobj))
(setq coords (list 
(list 640.5625 536.7646) 
(list 714.585 536.7146) 
(list 714.585 536.8916) 
(list 640.5625 536.8416)))
(apply 'command (append '("pline") coords '("c")))
(setq currobj (ssadd (entlast) currobj))
(setq coords (list 
(list 640.5625 536.9846) 
(list 714.585 537.0346) 
(list 714.585 537.2116) 
(list 640.5625 537.0616)))
(apply 'command (append '("pline") coords '("c")))
(setq currobj (ssadd (entlast) currobj))
(setq coords (list 
(list 640.5625 537.2046) 
(list 714.585 537.3546) 
(list 714.585 537.5316) 
(list 640.5625 537.2816)))
(apply 'command (append '("pline") coords '("c")))
(setq currobj (ssadd (entlast) currobj))
(setq coords (list 
(list 640.5625 537.4246) 
(list 714.585 537.6746) 
(list 714.585 537.8516) 
(list 640.5625 537.5016)))
(apply 'command (append '("pline") coords '("c")))
(setq currobj (ssadd (entlast) currobj))
(setq coords (list 
(list 640.5625 537.6446) 
(list 714.585 537.9946) 
(list 714.585 538.1716) 
(list 640.5625 537.7216)))
(apply 'command (append '("pline") coords '("c")))
(setq currobj (ssadd (entlast) currobj))
(setq coords (list 
(list 640.5625 537.8646) 
(list 714.585 538.3146) 
(list 714.585 538.4916) 
(list 640.5625 537.9416)))
(apply 'command (append '("pline") coords '("c")))
(setq currobj (ssadd (entlast) currobj))
(setq coords (list 
(list 640.5625 538.0846) 
(list 714.585 538.6346) 
(list 714.585 538.8116) 
(list 640.5625 538.1616)))
(apply 'command (append '("pline") coords '("c")))
(setq currobj (ssadd (entlast) currobj))
(setq coords (list 
(list 640.5625 538.3046) 
(list 714.585 538.9546) 
(list 714.585 539.1316) 
(list 640.5625 538.3816)))
(apply 'command (append '("pline") coords '("c")))
(setq currobj (ssadd (entlast) currobj))
(setq coords (list 
(list 639.4375 538.3816) 
(list 565.415 539.1316) 
(list 565.415 538.9546) 
(list 639.4375 538.3046)))
(apply 'command (append '("pline") coords '("c")))
(setq currobj (ssadd (entlast) currobj))
(setq coords (list 
(list 639.4375 538.1616) 
(list 565.415 538.8116) 
(list 565.415 538.6346) 
(list 639.4375 538.0846)))
(apply 'command (append '("pline") coords '("c")))
(setq currobj (ssadd (entlast) currobj))
(setq coords (list 
(list 639.4375 537.9416) 
(list 565.415 538.4916) 
(list 565.415 538.3146) 
(list 639.4375 537.8646)))
(apply 'command (append '("pline") coords '("c")))
(setq currobj (ssadd (entlast) currobj))
(setq coords (list 
(list 639.4375 537.7216) 
(list 565.415 538.1716) 
(list 565.415 537.9946) 
(list 639.4375 537.6446)))
(apply 'command (append '("pline") coords '("c")))
(setq currobj (ssadd (entlast) currobj))
(setq coords (list 
(list 639.4375 537.5016) 
(list 565.415 537.8516) 
(list 565.415 537.6746) 
(list 639.4375 537.4246)))
(apply 'command (append '("pline") coords '("c")))
(setq currobj (ssadd (entlast) currobj))
(setq coords (list 
(list 639.4375 537.2816) 
(list 565.415 537.5316) 
(list 565.415 537.3546) 
(list 639.4375 537.2046)))
(apply 'command (append '("pline") coords '("c")))
(setq currobj (ssadd (entlast) currobj))
(setq coords (list 
(list 639.4375 537.0616) 
(list 565.415 537.2116) 
(list 565.415 537.0346) 
(list 639.4375 536.9846)))
(apply 'command (append '("pline") coords '("c")))
(setq currobj (ssadd (entlast) currobj))
(setq coords (list 
(list 639.4375 536.8416) 
(list 565.415 536.8916) 
(list 565.415 536.7146) 
(list 639.4375 536.7646)))
(apply 'command (append '("pline") coords '("c")))
(setq currobj (ssadd (entlast) currobj))
(setq coords (list 
(list 639.4375 536.6216) 
(list 565.415 536.5716) 
(list 565.415 536.3946) 
(list 639.4375 536.5446)))
(apply 'command (append '("pline") coords '("c")))
(setq currobj (ssadd (entlast) currobj))
(setq coords (list 
(list 639.4375 536.4016) 
(list 565.415 536.2516) 
(list 565.415 536.0746) 
(list 639.4375 536.3246)))
(apply 'command (append '("pline") coords '("c")))
(setq currobj (ssadd (entlast) currobj))
(setq coords (list 
(list 639.4375 536.1816) 
(list 565.415 535.9316) 
(list 565.415 535.7546) 
(list 639.4375 536.1046)))
(apply 'command (append '("pline") coords '("c")))
(setq currobj (ssadd (entlast) currobj))
(setq coords (list 
(list 639.4375 535.9616) 
(list 565.415 535.6116) 
(list 565.415 535.4346) 
(list 639.4375 535.8846)))
(apply 'command (append '("pline") coords '("c")))
(setq currobj (ssadd (entlast) currobj))
(setq coords (list 
(list 639.4375 535.7416) 
(list 565.415 535.2916) 
(list 565.415 535.1146) 
(list 639.4375 535.6646)))
(apply 'command (append '("pline") coords '("c")))
(setq currobj (ssadd (entlast) currobj))
(setq coords (list 
(list 639.4375 535.5216) 
(list 565.415 534.9716) 
(list 565.415 534.7946) 
(list 639.4375 535.4446)))
(apply 'command (append '("pline") coords '("c")))
(setq currobj (ssadd (entlast) currobj))
(setq coords (list 
(list 639.4375 535.3016) 
(list 565.415 534.6516) 
(list 565.415 534.4746) 
(list 639.4375 535.2246)))
(apply 'command (append '("pline") coords '("c")))
(setq currobj (ssadd (entlast) currobj))
(command "_layer" "set" "nitride" "")
(command "_layer" "set" "text" "")
(command "_circle" "639.0625,524.0816" "0.075")
(command "_circle" "639.0625,524.3816" "0.075")
(command "_circle" "639.0625,524.6816" "0.075")
(command "_circle" "639.0625,524.9816" "0.075")
(command "_circle" "639.0625,525.2816" "0.075")
(command "_circle" "638.7625,524.0816" "0.075")
(command "_circle" "638.7625,524.3816" "0.075")
(command "_circle" "638.7625,524.6816" "0.075")
(command "_circle" "638.7625,524.9816" "0.075")
(command "_circle" "638.7625,525.2816" "0.075")
(command "_circle" "638.4625,524.0816" "0.075")
(command "_circle" "638.4625,524.3816" "0.075")
(command "_circle" "638.4625,524.6816" "0.075")
(command "_circle" "638.4625,524.9816" "0.075")
(command "_circle" "638.4625,525.2816" "0.075")
(command "_circle" "638.1625,524.0816" "0.075")
(command "_circle" "638.1625,524.3816" "0.075")
(command "_circle" "638.1625,524.6816" "0.075")
(command "_circle" "638.1625,524.9816" "0.075")
(command "_circle" "638.1625,525.2816" "0.075")
(command "_circle" "637.8625,524.0816" "0.075")
(command "_circle" "637.8625,524.3816" "0.075")
(command "_circle" "637.8625,524.6816" "0.075")
(command "_circle" "637.8625,524.9816" "0.075")
(command "_circle" "637.8625,525.2816" "0.075")
(command "_layer" "set" "nitride" "")
(setq coords (list 
(list 640.2625 549.5246) 
(list 640.2625 665.1693) 
(list 639.7375 665.1693) 
(list 639.7375 549.5246)))
(apply 'command (append '("pline") coords '("c")))
(setq currobj (ssadd (entlast) currobj))
(command "_layer" "set" "prebias" "")
(command "_rectangle" "639.7375,549.5246" "640.2625,665.1693")
(setq currobj (ssadd (entlast) currobj))
(command "_layer" "set" "nitride" "")
(setq coords (list 
(list 640.2625 665.1693) 
(list 640.5625 675.1693) 
(list 640.5625 675.1693) 
(list 640.5625 676.1693) 
(list 714.585 675.4193) 
(list 714.585 680.3623) 
(list 640.5625 679.6123) 
(list 640.5625 680.6123) 
(list 640.5625 680.6123) 
(list 640.2625 690.6123) 
(list 639.7375 690.6123) 
(list 639.4375 680.6123) 
(list 639.4375 680.6123) 
(list 639.4375 679.6123) 
(list 565.415 680.3623) 
(list 565.415 675.4193) 
(list 639.4375 676.1693) 
(list 639.4375 675.1693) 
(list 639.4375 675.1693) 
(list 639.7375 665.1693)))
(apply 'command (append '("pline") coords '("c")))
(setq currobj (ssadd (entlast) currobj))
(command "_layer" "set" "prebias" "")
(setq coords (list 
(list 639.4375 665.1693) 
(list 639.4375 676.1693) 
(list 565.415 675.4193) 
(list 565.415 680.3623) 
(list 639.4375 679.6123) 
(list 639.4375 690.6123) 
(list 640.5625 690.6123) 
(list 640.5625 679.6123) 
(list 714.585 680.3623) 
(list 714.585 675.4193) 
(list 640.5625 676.1693) 
(list 640.5625 665.1693)))
(apply 'command (append '("pline") coords '("c")))
(setq currobj (ssadd (entlast) currobj))
(command "_layer" "set" "nitride" "")
(command "_layer" "set" "fda1" "")
(setq coords (list 
(list 640.5625 676.3123) 
(list 714.585 675.5623) 
(list 714.585 675.7393) 
(list 640.5625 676.3893)))
(apply 'command (append '("pline") coords '("c")))
(setq currobj (ssadd (entlast) currobj))
(setq coords (list 
(list 640.5625 676.5323) 
(list 714.585 675.8823) 
(list 714.585 676.0593) 
(list 640.5625 676.6093)))
(apply 'command (append '("pline") coords '("c")))
(setq currobj (ssadd (entlast) currobj))
(setq coords (list 
(list 640.5625 676.7523) 
(list 714.585 676.2023) 
(list 714.585 676.3793) 
(list 640.5625 676.8293)))
(apply 'command (append '("pline") coords '("c")))
(setq currobj (ssadd (entlast) currobj))
(setq coords (list 
(list 640.5625 676.9723) 
(list 714.585 676.5223) 
(list 714.585 676.6993) 
(list 640.5625 677.0493)))
(apply 'command (append '("pline") coords '("c")))
(setq currobj (ssadd (entlast) currobj))
(setq coords (list 
(list 640.5625 677.1923) 
(list 714.585 676.8423) 
(list 714.585 677.0193) 
(list 640.5625 677.2693)))
(apply 'command (append '("pline") coords '("c")))
(setq currobj (ssadd (entlast) currobj))
(setq coords (list 
(list 640.5625 677.4123) 
(list 714.585 677.1623) 
(list 714.585 677.3393) 
(list 640.5625 677.4893)))
(apply 'command (append '("pline") coords '("c")))
(setq currobj (ssadd (entlast) currobj))
(setq coords (list 
(list 640.5625 677.6323) 
(list 714.585 677.4823) 
(list 714.585 677.6593) 
(list 640.5625 677.7093)))
(apply 'command (append '("pline") coords '("c")))
(setq currobj (ssadd (entlast) currobj))
(setq coords (list 
(list 640.5625 677.8523) 
(list 714.585 677.8023) 
(list 714.585 677.9793) 
(list 640.5625 677.9293)))
(apply 'command (append '("pline") coords '("c")))
(setq currobj (ssadd (entlast) currobj))
(setq coords (list 
(list 640.5625 678.0723) 
(list 714.585 678.1223) 
(list 714.585 678.2993) 
(list 640.5625 678.1493)))
(apply 'command (append '("pline") coords '("c")))
(setq currobj (ssadd (entlast) currobj))
(setq coords (list 
(list 640.5625 678.2923) 
(list 714.585 678.4423) 
(list 714.585 678.6193) 
(list 640.5625 678.3693)))
(apply 'command (append '("pline") coords '("c")))
(setq currobj (ssadd (entlast) currobj))
(setq coords (list 
(list 640.5625 678.5123) 
(list 714.585 678.7623) 
(list 714.585 678.9393) 
(list 640.5625 678.5893)))
(apply 'command (append '("pline") coords '("c")))
(setq currobj (ssadd (entlast) currobj))
(setq coords (list 
(list 640.5625 678.7323) 
(list 714.585 679.0823) 
(list 714.585 679.2593) 
(list 640.5625 678.8093)))
(apply 'command (append '("pline") coords '("c")))
(setq currobj (ssadd (entlast) currobj))
(setq coords (list 
(list 640.5625 678.9523) 
(list 714.585 679.4023) 
(list 714.585 679.5793) 
(list 640.5625 679.0293)))
(apply 'command (append '("pline") coords '("c")))
(setq currobj (ssadd (entlast) currobj))
(setq coords (list 
(list 640.5625 679.1723) 
(list 714.585 679.7223) 
(list 714.585 679.8993) 
(list 640.5625 679.2493)))
(apply 'command (append '("pline") coords '("c")))
(setq currobj (ssadd (entlast) currobj))
(setq coords (list 
(list 640.5625 679.3923) 
(list 714.585 680.0423) 
(list 714.585 680.2193) 
(list 640.5625 679.4693)))
(apply 'command (append '("pline") coords '("c")))
(setq currobj (ssadd (entlast) currobj))
(setq coords (list 
(list 639.4375 679.4693) 
(list 565.415 680.2193) 
(list 565.415 680.0423) 
(list 639.4375 679.3923)))
(apply 'command (append '("pline") coords '("c")))
(setq currobj (ssadd (entlast) currobj))
(setq coords (list 
(list 639.4375 679.2493) 
(list 565.415 679.8993) 
(list 565.415 679.7223) 
(list 639.4375 679.1723)))
(apply 'command (append '("pline") coords '("c")))
(setq currobj (ssadd (entlast) currobj))
(setq coords (list 
(list 639.4375 679.0293) 
(list 565.415 679.5793) 
(list 565.415 679.4023) 
(list 639.4375 678.9523)))
(apply 'command (append '("pline") coords '("c")))
(setq currobj (ssadd (entlast) currobj))
(setq coords (list 
(list 639.4375 678.8093) 
(list 565.415 679.2593) 
(list 565.415 679.0823) 
(list 639.4375 678.7323)))
(apply 'command (append '("pline") coords '("c")))
(setq currobj (ssadd (entlast) currobj))
(setq coords (list 
(list 639.4375 678.5893) 
(list 565.415 678.9393) 
(list 565.415 678.7623) 
(list 639.4375 678.5123)))
(apply 'command (append '("pline") coords '("c")))
(setq currobj (ssadd (entlast) currobj))
(setq coords (list 
(list 639.4375 678.3693) 
(list 565.415 678.6193) 
(list 565.415 678.4423) 
(list 639.4375 678.2923)))
(apply 'command (append '("pline") coords '("c")))
(setq currobj (ssadd (entlast) currobj))
(setq coords (list 
(list 639.4375 678.1493) 
(list 565.415 678.2993) 
(list 565.415 678.1223) 
(list 639.4375 678.0723)))
(apply 'command (append '("pline") coords '("c")))
(setq currobj (ssadd (entlast) currobj))
(setq coords (list 
(list 639.4375 677.9293) 
(list 565.415 677.9793) 
(list 565.415 677.8023) 
(list 639.4375 677.8523)))
(apply 'command (append '("pline") coords '("c")))
(setq currobj (ssadd (entlast) currobj))
(setq coords (list 
(list 639.4375 677.7093) 
(list 565.415 677.6593) 
(list 565.415 677.4823) 
(list 639.4375 677.6323)))
(apply 'command (append '("pline") coords '("c")))
(setq currobj (ssadd (entlast) currobj))
(setq coords (list 
(list 639.4375 677.4893) 
(list 565.415 677.3393) 
(list 565.415 677.1623) 
(list 639.4375 677.4123)))
(apply 'command (append '("pline") coords '("c")))
(setq currobj (ssadd (entlast) currobj))
(setq coords (list 
(list 639.4375 677.2693) 
(list 565.415 677.0193) 
(list 565.415 676.8423) 
(list 639.4375 677.1923)))
(apply 'command (append '("pline") coords '("c")))
(setq currobj (ssadd (entlast) currobj))
(setq coords (list 
(list 639.4375 677.0493) 
(list 565.415 676.6993) 
(list 565.415 676.5223) 
(list 639.4375 676.9723)))
(apply 'command (append '("pline") coords '("c")))
(setq currobj (ssadd (entlast) currobj))
(setq coords (list 
(list 639.4375 676.8293) 
(list 565.415 676.3793) 
(list 565.415 676.2023) 
(list 639.4375 676.7523)))
(apply 'command (append '("pline") coords '("c")))
(setq currobj (ssadd (entlast) currobj))
(setq coords (list 
(list 639.4375 676.6093) 
(list 565.415 676.0593) 
(list 565.415 675.8823) 
(list 639.4375 676.5323)))
(apply 'command (append '("pline") coords '("c")))
(setq currobj (ssadd (entlast) currobj))
(setq coords (list 
(list 639.4375 676.3893) 
(list 565.415 675.7393) 
(list 565.415 675.5623) 
(list 639.4375 676.3123)))
(apply 'command (append '("pline") coords '("c")))
(setq currobj (ssadd (entlast) currobj))
(command "_layer" "set" "nitride" "")
(command "_layer" "set" "text" "")
(command "_circle" "639.0625,665.1693" "0.075")
(command "_circle" "639.0625,665.4693" "0.075")
(command "_circle" "639.0625,665.7693" "0.075")
(command "_circle" "639.0625,666.0693" "0.075")
(command "_circle" "639.0625,666.3693" "0.075")
(command "_circle" "638.7625,665.1693" "0.075")
(command "_circle" "638.7625,665.4693" "0.075")
(command "_circle" "638.7625,665.7693" "0.075")
(command "_circle" "638.7625,666.0693" "0.075")
(command "_circle" "638.7625,666.3693" "0.075")
(command "_circle" "638.4625,665.1693" "0.075")
(command "_circle" "638.4625,665.4693" "0.075")
(command "_circle" "638.4625,665.7693" "0.075")
(command "_circle" "638.4625,666.0693" "0.075")
(command "_circle" "638.4625,666.3693" "0.075")
(command "_circle" "638.1625,665.1693" "0.075")
(command "_circle" "638.1625,665.4693" "0.075")
(command "_circle" "638.1625,665.7693" "0.075")
(command "_circle" "638.1625,666.0693" "0.075")
(command "_circle" "638.1625,666.3693" "0.075")
(command "_circle" "637.8625,665.1693" "0.075")
(command "_circle" "637.8625,665.4693" "0.075")
(command "_circle" "637.8625,665.7693" "0.075")
(command "_circle" "637.8625,666.0693" "0.075")
(command "_circle" "637.8625,666.3693" "0.075")
(command "_layer" "set" "nitride" "")
(setq coords (list 
(list 640.2625 690.6123) 
(list 640.2625 806.257) 
(list 639.7375 806.257) 
(list 639.7375 690.6123)))
(apply 'command (append '("pline") coords '("c")))
(setq currobj (ssadd (entlast) currobj))
(command "_layer" "set" "prebias" "")
(command "_rectangle" "639.7375,690.6123" "640.2625,806.257")
(setq currobj (ssadd (entlast) currobj))
(command "_layer" "set" "nitride" "")
(setq coords (list 
(list 640.2625 806.257) 
(list 640.5625 816.257) 
(list 640.5625 816.257) 
(list 640.5625 817.257) 
(list 714.585 816.507) 
(list 714.585 821.45) 
(list 640.5625 820.7) 
(list 640.5625 821.7) 
(list 640.5625 821.7) 
(list 640.2625 831.7) 
(list 639.7375 831.7) 
(list 639.4375 821.7) 
(list 639.4375 821.7) 
(list 639.4375 820.7) 
(list 565.415 821.45) 
(list 565.415 816.507) 
(list 639.4375 817.257) 
(list 639.4375 816.257) 
(list 639.4375 816.257) 
(list 639.7375 806.257)))
(apply 'command (append '("pline") coords '("c")))
(setq currobj (ssadd (entlast) currobj))
(command "_layer" "set" "prebias" "")
(setq coords (list 
(list 639.4375 806.257) 
(list 639.4375 817.257) 
(list 565.415 816.507) 
(list 565.415 821.45) 
(list 639.4375 820.7) 
(list 639.4375 831.7) 
(list 640.5625 831.7) 
(list 640.5625 820.7) 
(list 714.585 821.45) 
(list 714.585 816.507) 
(list 640.5625 817.257) 
(list 640.5625 806.257)))
(apply 'command (append '("pline") coords '("c")))
(setq currobj (ssadd (entlast) currobj))
(command "_layer" "set" "nitride" "")
(command "_layer" "set" "fda1" "")
(setq coords (list 
(list 640.5625 817.4) 
(list 714.585 816.65) 
(list 714.585 816.827) 
(list 640.5625 817.477)))
(apply 'command (append '("pline") coords '("c")))
(setq currobj (ssadd (entlast) currobj))
(setq coords (list 
(list 640.5625 817.62) 
(list 714.585 816.97) 
(list 714.585 817.147) 
(list 640.5625 817.697)))
(apply 'command (append '("pline") coords '("c")))
(setq currobj (ssadd (entlast) currobj))
(setq coords (list 
(list 640.5625 817.84) 
(list 714.585 817.29) 
(list 714.585 817.467) 
(list 640.5625 817.917)))
(apply 'command (append '("pline") coords '("c")))
(setq currobj (ssadd (entlast) currobj))
(setq coords (list 
(list 640.5625 818.06) 
(list 714.585 817.61) 
(list 714.585 817.787) 
(list 640.5625 818.137)))
(apply 'command (append '("pline") coords '("c")))
(setq currobj (ssadd (entlast) currobj))
(setq coords (list 
(list 640.5625 818.28) 
(list 714.585 817.93) 
(list 714.585 818.107) 
(list 640.5625 818.357)))
(apply 'command (append '("pline") coords '("c")))
(setq currobj (ssadd (entlast) currobj))
(setq coords (list 
(list 640.5625 818.5) 
(list 714.585 818.25) 
(list 714.585 818.427) 
(list 640.5625 818.577)))
(apply 'command (append '("pline") coords '("c")))
(setq currobj (ssadd (entlast) currobj))
(setq coords (list 
(list 640.5625 818.72) 
(list 714.585 818.57) 
(list 714.585 818.747) 
(list 640.5625 818.797)))
(apply 'command (append '("pline") coords '("c")))
(setq currobj (ssadd (entlast) currobj))
(setq coords (list 
(list 640.5625 818.94) 
(list 714.585 818.89) 
(list 714.585 819.067) 
(list 640.5625 819.017)))
(apply 'command (append '("pline") coords '("c")))
(setq currobj (ssadd (entlast) currobj))
(setq coords (list 
(list 640.5625 819.16) 
(list 714.585 819.21) 
(list 714.585 819.387) 
(list 640.5625 819.237)))
(apply 'command (append '("pline") coords '("c")))
(setq currobj (ssadd (entlast) currobj))
(setq coords (list 
(list 640.5625 819.38) 
(list 714.585 819.53) 
(list 714.585 819.707) 
(list 640.5625 819.457)))
(apply 'command (append '("pline") coords '("c")))
(setq currobj (ssadd (entlast) currobj))
(setq coords (list 
(list 640.5625 819.6) 
(list 714.585 819.85) 
(list 714.585 820.027) 
(list 640.5625 819.677)))
(apply 'command (append '("pline") coords '("c")))
(setq currobj (ssadd (entlast) currobj))
(setq coords (list 
(list 640.5625 819.82) 
(list 714.585 820.17) 
(list 714.585 820.347) 
(list 640.5625 819.897)))
(apply 'command (append '("pline") coords '("c")))
(setq currobj (ssadd (entlast) currobj))
(setq coords (list 
(list 640.5625 820.04) 
(list 714.585 820.49) 
(list 714.585 820.667) 
(list 640.5625 820.117)))
(apply 'command (append '("pline") coords '("c")))
(setq currobj (ssadd (entlast) currobj))
(setq coords (list 
(list 640.5625 820.26) 
(list 714.585 820.81) 
(list 714.585 820.987) 
(list 640.5625 820.337)))
(apply 'command (append '("pline") coords '("c")))
(setq currobj (ssadd (entlast) currobj))
(setq coords (list 
(list 640.5625 820.48) 
(list 714.585 821.13) 
(list 714.585 821.307) 
(list 640.5625 820.557)))
(apply 'command (append '("pline") coords '("c")))
(setq currobj (ssadd (entlast) currobj))
(setq coords (list 
(list 639.4375 820.557) 
(list 565.415 821.307) 
(list 565.415 821.13) 
(list 639.4375 820.48)))
(apply 'command (append '("pline") coords '("c")))
(setq currobj (ssadd (entlast) currobj))
(setq coords (list 
(list 639.4375 820.337) 
(list 565.415 820.987) 
(list 565.415 820.81) 
(list 639.4375 820.26)))
(apply 'command (append '("pline") coords '("c")))
(setq currobj (ssadd (entlast) currobj))
(setq coords (list 
(list 639.4375 820.117) 
(list 565.415 820.667) 
(list 565.415 820.49) 
(list 639.4375 820.04)))
(apply 'command (append '("pline") coords '("c")))
(setq currobj (ssadd (entlast) currobj))
(setq coords (list 
(list 639.4375 819.897) 
(list 565.415 820.347) 
(list 565.415 820.17) 
(list 639.4375 819.82)))
(apply 'command (append '("pline") coords '("c")))
(setq currobj (ssadd (entlast) currobj))
(setq coords (list 
(list 639.4375 819.677) 
(list 565.415 820.027) 
(list 565.415 819.85) 
(list 639.4375 819.6)))
(apply 'command (append '("pline") coords '("c")))
(setq currobj (ssadd (entlast) currobj))
(setq coords (list 
(list 639.4375 819.457) 
(list 565.415 819.707) 
(list 565.415 819.53) 
(list 639.4375 819.38)))
(apply 'command (append '("pline") coords '("c")))
(setq currobj (ssadd (entlast) currobj))
(setq coords (list 
(list 639.4375 819.237) 
(list 565.415 819.387) 
(list 565.415 819.21) 
(list 639.4375 819.16)))
(apply 'command (append '("pline") coords '("c")))
(setq currobj (ssadd (entlast) currobj))
(setq coords (list 
(list 639.4375 819.017) 
(list 565.415 819.067) 
(list 565.415 818.89) 
(list 639.4375 818.94)))
(apply 'command (append '("pline") coords '("c")))
(setq currobj (ssadd (entlast) currobj))
(setq coords (list 
(list 639.4375 818.797) 
(list 565.415 818.747) 
(list 565.415 818.57) 
(list 639.4375 818.72)))
(apply 'command (append '("pline") coords '("c")))
(setq currobj (ssadd (entlast) currobj))
(setq coords (list 
(list 639.4375 818.577) 
(list 565.415 818.427) 
(list 565.415 818.25) 
(list 639.4375 818.5)))
(apply 'command (append '("pline") coords '("c")))
(setq currobj (ssadd (entlast) currobj))
(setq coords (list 
(list 639.4375 818.357) 
(list 565.415 818.107) 
(list 565.415 817.93) 
(list 639.4375 818.28)))
(apply 'command (append '("pline") coords '("c")))
(setq currobj (ssadd (entlast) currobj))
(setq coords (list 
(list 639.4375 818.137) 
(list 565.415 817.787) 
(list 565.415 817.61) 
(list 639.4375 818.06)))
(apply 'command (append '("pline") coords '("c")))
(setq currobj (ssadd (entlast) currobj))
(setq coords (list 
(list 639.4375 817.917) 
(list 565.415 817.467) 
(list 565.415 817.29) 
(list 639.4375 817.84)))
(apply 'command (append '("pline") coords '("c")))
(setq currobj (ssadd (entlast) currobj))
(setq coords (list 
(list 639.4375 817.697) 
(list 565.415 817.147) 
(list 565.415 816.97) 
(list 639.4375 817.62)))
(apply 'command (append '("pline") coords '("c")))
(setq currobj (ssadd (entlast) currobj))
(setq coords (list 
(list 639.4375 817.477) 
(list 565.415 816.827) 
(list 565.415 816.65) 
(list 639.4375 817.4)))
(apply 'command (append '("pline") coords '("c")))
(setq currobj (ssadd (entlast) currobj))
(command "_layer" "set" "nitride" "")
(command "_layer" "set" "text" "")
(command "_circle" "639.0625,806.257" "0.075")
(command "_circle" "639.0625,806.557" "0.075")
(command "_circle" "639.0625,806.857" "0.075")
(command "_circle" "639.0625,807.157" "0.075")
(command "_circle" "639.0625,807.457" "0.075")
(command "_circle" "638.7625,806.257" "0.075")
(command "_circle" "638.7625,806.557" "0.075")
(command "_circle" "638.7625,806.857" "0.075")
(command "_circle" "638.7625,807.157" "0.075")
(command "_circle" "638.7625,807.457" "0.075")
(command "_circle" "638.4625,806.257" "0.075")
(command "_circle" "638.4625,806.557" "0.075")
(command "_circle" "638.4625,806.857" "0.075")
(command "_circle" "638.4625,807.157" "0.075")
(command "_circle" "638.4625,807.457" "0.075")
(command "_circle" "638.1625,806.257" "0.075")
(command "_circle" "638.1625,806.557" "0.075")
(command "_circle" "638.1625,806.857" "0.075")
(command "_circle" "638.1625,807.157" "0.075")
(command "_circle" "638.1625,807.457" "0.075")
(command "_circle" "637.8625,806.257" "0.075")
(command "_circle" "637.8625,806.557" "0.075")
(command "_circle" "637.8625,806.857" "0.075")
(command "_circle" "637.8625,807.157" "0.075")
(command "_circle" "637.8625,807.457" "0.075")
(command "_layer" "set" "nitride" "")
(setq coords (list 
(list 640.2625 831.7) 
(list 640.2625 836.7) 
(list 639.7375 836.7) 
(list 639.7375 831.7)))
(apply 'command (append '("pline") coords '("c")))
(setq currobj (ssadd (entlast) currobj))
(command "_layer" "set" "prebias" "")
(command "_rectangle" "639.7375,831.7" "640.2625,836.7")
(setq currobj (ssadd (entlast) currobj))
(command "_layer" "set" "nitride" "")
(setq cooledsinglenanobeam2 currobj)
(setq currobj nil)
(setq currobj (ssadd))
; DRAWING PHOTONIC CRYSTAL
(command "_layer" "set" "negYjunc" "")
(setq coords (list 
(list 640.135 866.7) 
(list 640 851.7) 
(list 640 866.7)))
(apply 'command (append '("pline") coords '("c")))
(setq currobj (ssadd (entlast) currobj))
(setq coords (list 
(list 640.2625 836.7) 
(list 640.415 866.7) 
(list 641.076 866.7) 
(list 641.076 836.7)))
(apply 'command (append '("pline") coords '("c")))
(setq currobj (ssadd (entlast) currobj))
(setq coords (list 
(list 639.865 866.7) 
(list 640 851.7) 
(list 640 866.7)))
(apply 'command (append '("pline") coords '("c")))
(setq currobj (ssadd (entlast) currobj))
(setq coords (list 
(list 639.7375 836.7) 
(list 639.585 866.7) 
(list 638.924 866.7) 
(list 638.924 836.7)))
(apply 'command (append '("pline") coords '("c")))
(setq currobj (ssadd (entlast) currobj))
(command "_layer" "set" "nitride" "")
(setq yjunction2 currobj)
(setq currobj nil)
(setq currobj (ssadd))
(setq tap2 nil)
(setq tap2 (ssadd))
(command "_layer" "set" "phc" "")
(setq coords (list 
(list 640 866.7) 
(list 640.135 866.7) 
(list 640.135 866.7103) 
(list 640.135 866.7206) 
(list 640.135 866.7308) 
(list 640.135 866.7411) 
(list 640.135 866.7514) 
(list 640.135 866.7617) 
(list 640.135 866.7719) 
(list 640.135 866.7822) 
(list 640.135 866.7925) 
(list 640.135 866.8028) 
(list 640.135 866.8131) 
(list 640.135 866.8233) 
(list 640.135 866.8336) 
(list 640.135 866.8439) 
(list 640.135 866.8542) 
(list 640.135 866.8644) 
(list 640.135 866.8747) 
(list 640.135 866.885) 
(list 640.135 866.8953) 
(list 640.135 866.9056) 
(list 640.135 866.9158) 
(list 640.135 866.9261) 
(list 640.135 866.9364) 
(list 640.135 866.9467) 
(list 640.135 866.9569) 
(list 640.135 866.9672) 
(list 640.135 866.9775) 
(list 640.135 866.9878) 
(list 640.135 866.9981) 
(list 640.135 867.0083) 
(list 640.135 867.0186) 
(list 640.135 867.0289) 
(list 640.135 867.0392) 
(list 640.135 867.0494) 
(list 640.135 867.0597) 
(list 640.135 867.07) 
(list 640 867.07)))
(apply 'command (append '("pline") coords '("c")))
(setq tap2 (ssadd (entlast) tap2))
(command "_mirror" (entlast) "" "640,900" "640,901" "No")
(setq tap2 (ssadd (entlast) tap2))
(setq coords (list 
(list 640.4232 866.7) 
(list 640.415 866.7) 
(list 640.4152 866.7103) 
(list 640.4154 866.7206) 
(list 640.4156 866.7308) 
(list 640.4157 866.7411) 
(list 640.4157 866.7514) 
(list 640.4157 866.7617) 
(list 640.4155 866.7719) 
(list 640.4153 866.7822) 
(list 640.4149 866.7925) 
(list 640.4145 866.8028) 
(list 640.414 866.8131) 
(list 640.4135 866.8233) 
(list 640.4129 866.8336) 
(list 640.4124 866.8439) 
(list 640.4118 866.8542) 
(list 640.4113 866.8644) 
(list 640.4109 866.8747) 
(list 640.4106 866.885) 
(list 640.4105 866.8953) 
(list 640.4104 866.9056) 
(list 640.4106 866.9158) 
(list 640.4109 866.9261) 
(list 640.4114 866.9364) 
(list 640.412 866.9467) 
(list 640.4128 866.9569) 
(list 640.4137 866.9672) 
(list 640.4148 866.9775) 
(list 640.4159 866.9878) 
(list 640.4171 866.9981) 
(list 640.4183 867.0083) 
(list 640.4195 867.0186) 
(list 640.4205 867.0289) 
(list 640.4215 867.0392) 
(list 640.4223 867.0494) 
(list 640.4228 867.0597) 
(list 640.4232 867.07) 
(list 640.4232 867.07)))
(apply 'command (append '("pline") coords '("c")))
(setq tap2 (ssadd (entlast) tap2))
(command "_mirror" (entlast) "" "640,900" "640,901" "No")
(setq tap2 (ssadd (entlast) tap2))
(setq coords (list 
(list 641.076 866.7) 
(list 640.4232 866.7) 
(list 640.4232 866.7103) 
(list 640.4232 866.7206) 
(list 640.4232 866.7308) 
(list 640.4232 866.7411) 
(list 640.4232 866.7514) 
(list 640.4232 866.7617) 
(list 640.4232 866.7719) 
(list 640.4232 866.7822) 
(list 640.4232 866.7925) 
(list 640.4232 866.8028) 
(list 640.4232 866.8131) 
(list 640.4232 866.8233) 
(list 640.4232 866.8336) 
(list 640.4232 866.8439) 
(list 640.4232 866.8542) 
(list 640.4232 866.8644) 
(list 640.4232 866.8747) 
(list 640.4232 866.885) 
(list 640.4232 866.8953) 
(list 640.4232 866.9056) 
(list 640.4232 866.9158) 
(list 640.4232 866.9261) 
(list 640.4232 866.9364) 
(list 640.4232 866.9467) 
(list 640.4232 866.9569) 
(list 640.4232 866.9672) 
(list 640.4232 866.9775) 
(list 640.4232 866.9878) 
(list 640.4232 866.9981) 
(list 640.4232 867.0083) 
(list 640.4232 867.0186) 
(list 640.4232 867.0289) 
(list 640.4232 867.0392) 
(list 640.4232 867.0494) 
(list 640.4232 867.0597) 
(list 640.4232 867.07) 
(list 641.076 867.07)))
(apply 'command (append '("pline") coords '("c")))
(setq tap2 (ssadd (entlast) tap2))
(command "_mirror" (entlast) "" "640,900" "640,901" "No")
(setq tap2 (ssadd (entlast) tap2))
(setq coords (list 
(list 640 867.07) 
(list 640.135 867.07) 
(list 640.135 867.0803) 
(list 640.135 867.0906) 
(list 640.135 867.1008) 
(list 640.135 867.1111) 
(list 640.135 867.1214) 
(list 640.135 867.1317) 
(list 640.135 867.1419) 
(list 640.135 867.1522) 
(list 640.135 867.1625) 
(list 640.135 867.1728) 
(list 640.135 867.1831) 
(list 640.135 867.1933) 
(list 640.135 867.2036) 
(list 640.135 867.2139) 
(list 640.135 867.2242) 
(list 640.135 867.2344) 
(list 640.135 867.2447) 
(list 640.135 867.255) 
(list 640.135 867.2653) 
(list 640.135 867.2756) 
(list 640.135 867.2858) 
(list 640.135 867.2961) 
(list 640.135 867.3064) 
(list 640.135 867.3167) 
(list 640.135 867.3269) 
(list 640.135 867.3372) 
(list 640.135 867.3475) 
(list 640.135 867.3578) 
(list 640.135 867.3681) 
(list 640.135 867.3783) 
(list 640.135 867.3886) 
(list 640.135 867.3989) 
(list 640.135 867.4092) 
(list 640.135 867.4194) 
(list 640.135 867.4297) 
(list 640.135 867.44) 
(list 640 867.44)))
(apply 'command (append '("pline") coords '("c")))
(setq tap2 (ssadd (entlast) tap2))
(command "_mirror" (entlast) "" "640,900" "640,901" "No")
(setq tap2 (ssadd (entlast) tap2))
(setq coords (list 
(list 640.4314 867.07) 
(list 640.4232 867.07) 
(list 640.4233 867.0803) 
(list 640.4231 867.0906) 
(list 640.4227 867.1008) 
(list 640.4219 867.1111) 
(list 640.4209 867.1214) 
(list 640.4196 867.1317) 
(list 640.4181 867.1419) 
(list 640.4165 867.1522) 
(list 640.4147 867.1625) 
(list 640.4128 867.1728) 
(list 640.4109 867.1831) 
(list 640.409 867.1933) 
(list 640.4072 867.2036) 
(list 640.4056 867.2139) 
(list 640.4042 867.2242) 
(list 640.4031 867.2344) 
(list 640.4023 867.2447) 
(list 640.4019 867.255) 
(list 640.4019 867.2653) 
(list 640.4022 867.2756) 
(list 640.403 867.2858) 
(list 640.4041 867.2961) 
(list 640.4056 867.3064) 
(list 640.4075 867.3167) 
(list 640.4096 867.3269) 
(list 640.412 867.3372) 
(list 640.4145 867.3475) 
(list 640.4171 867.3578) 
(list 640.4197 867.3681) 
(list 640.4223 867.3783) 
(list 640.4246 867.3886) 
(list 640.4267 867.3989) 
(list 640.4285 867.4092) 
(list 640.43 867.4194) 
(list 640.4309 867.4297) 
(list 640.4314 867.44) 
(list 640.4314 867.44)))
(apply 'command (append '("pline") coords '("c")))
(setq tap2 (ssadd (entlast) tap2))
(command "_mirror" (entlast) "" "640,900" "640,901" "No")
(setq tap2 (ssadd (entlast) tap2))
(setq coords (list 
(list 641.076 867.07) 
(list 640.4314 867.07) 
(list 640.4314 867.0803) 
(list 640.4314 867.0906) 
(list 640.4314 867.1008) 
(list 640.4314 867.1111) 
(list 640.4314 867.1214) 
(list 640.4314 867.1317) 
(list 640.4314 867.1419) 
(list 640.4314 867.1522) 
(list 640.4314 867.1625) 
(list 640.4314 867.1728) 
(list 640.4314 867.1831) 
(list 640.4314 867.1933) 
(list 640.4314 867.2036) 
(list 640.4314 867.2139) 
(list 640.4314 867.2242) 
(list 640.4314 867.2344) 
(list 640.4314 867.2447) 
(list 640.4314 867.255) 
(list 640.4314 867.2653) 
(list 640.4314 867.2756) 
(list 640.4314 867.2858) 
(list 640.4314 867.2961) 
(list 640.4314 867.3064) 
(list 640.4314 867.3167) 
(list 640.4314 867.3269) 
(list 640.4314 867.3372) 
(list 640.4314 867.3475) 
(list 640.4314 867.3578) 
(list 640.4314 867.3681) 
(list 640.4314 867.3783) 
(list 640.4314 867.3886) 
(list 640.4314 867.3989) 
(list 640.4314 867.4092) 
(list 640.4314 867.4194) 
(list 640.4314 867.4297) 
(list 640.4314 867.44) 
(list 641.076 867.44)))
(apply 'command (append '("pline") coords '("c")))
(setq tap2 (ssadd (entlast) tap2))
(command "_mirror" (entlast) "" "640,900" "640,901" "No")
(setq tap2 (ssadd (entlast) tap2))
(setq coords (list 
(list 640 867.44) 
(list 640.135 867.44) 
(list 640.135 867.4503) 
(list 640.135 867.4606) 
(list 640.135 867.4708) 
(list 640.135 867.4811) 
(list 640.135 867.4914) 
(list 640.135 867.5017) 
(list 640.135 867.5119) 
(list 640.135 867.5222) 
(list 640.135 867.5325) 
(list 640.135 867.5428) 
(list 640.135 867.5531) 
(list 640.135 867.5633) 
(list 640.135 867.5736) 
(list 640.135 867.5839) 
(list 640.135 867.5942) 
(list 640.135 867.6044) 
(list 640.135 867.6147) 
(list 640.135 867.625) 
(list 640.135 867.6353) 
(list 640.135 867.6456) 
(list 640.135 867.6558) 
(list 640.135 867.6661) 
(list 640.135 867.6764) 
(list 640.135 867.6867) 
(list 640.135 867.6969) 
(list 640.135 867.7072) 
(list 640.135 867.7175) 
(list 640.135 867.7278) 
(list 640.135 867.7381) 
(list 640.135 867.7483) 
(list 640.135 867.7586) 
(list 640.135 867.7689) 
(list 640.135 867.7792) 
(list 640.135 867.7894) 
(list 640.135 867.7997) 
(list 640.135 867.81) 
(list 640 867.81)))
(apply 'command (append '("pline") coords '("c")))
(setq tap2 (ssadd (entlast) tap2))
(command "_mirror" (entlast) "" "640,900" "640,901" "No")
(setq tap2 (ssadd (entlast) tap2))
(setq coords (list 
(list 640.4396 867.44) 
(list 640.4314 867.44) 
(list 640.4314 867.4503) 
(list 640.4308 867.4606) 
(list 640.4297 867.4708) 
(list 640.4281 867.4811) 
(list 640.4261 867.4914) 
(list 640.4236 867.5017) 
(list 640.4208 867.5119) 
(list 640.4177 867.5222) 
(list 640.4144 867.5325) 
(list 640.411 867.5428) 
(list 640.4077 867.5531) 
(list 640.4045 867.5633) 
(list 640.4015 867.5736) 
(list 640.3989 867.5839) 
(list 640.3966 867.5942) 
(list 640.3949 867.6044) 
(list 640.3937 867.6147) 
(list 640.3932 867.625) 
(list 640.3932 867.6353) 
(list 640.394 867.6456) 
(list 640.3954 867.6558) 
(list 640.3974 867.6661) 
(list 640.3999 867.6764) 
(list 640.403 867.6867) 
(list 640.4065 867.6969) 
(list 640.4103 867.7072) 
(list 640.4143 867.7175) 
(list 640.4183 867.7278) 
(list 640.4224 867.7381) 
(list 640.4262 867.7483) 
(list 640.4298 867.7586) 
(list 640.433 867.7689) 
(list 640.4356 867.7792) 
(list 640.4376 867.7894) 
(list 640.439 867.7997) 
(list 640.4396 867.81) 
(list 640.4396 867.81)))
(apply 'command (append '("pline") coords '("c")))
(setq tap2 (ssadd (entlast) tap2))
(command "_mirror" (entlast) "" "640,900" "640,901" "No")
(setq tap2 (ssadd (entlast) tap2))
(setq coords (list 
(list 641.076 867.44) 
(list 640.4396 867.44) 
(list 640.4396 867.4503) 
(list 640.4396 867.4606) 
(list 640.4396 867.4708) 
(list 640.4396 867.4811) 
(list 640.4396 867.4914) 
(list 640.4396 867.5017) 
(list 640.4396 867.5119) 
(list 640.4396 867.5222) 
(list 640.4396 867.5325) 
(list 640.4396 867.5428) 
(list 640.4396 867.5531) 
(list 640.4396 867.5633) 
(list 640.4396 867.5736) 
(list 640.4396 867.5839) 
(list 640.4396 867.5942) 
(list 640.4396 867.6044) 
(list 640.4396 867.6147) 
(list 640.4396 867.625) 
(list 640.4396 867.6353) 
(list 640.4396 867.6456) 
(list 640.4396 867.6558) 
(list 640.4396 867.6661) 
(list 640.4396 867.6764) 
(list 640.4396 867.6867) 
(list 640.4396 867.6969) 
(list 640.4396 867.7072) 
(list 640.4396 867.7175) 
(list 640.4396 867.7278) 
(list 640.4396 867.7381) 
(list 640.4396 867.7483) 
(list 640.4396 867.7586) 
(list 640.4396 867.7689) 
(list 640.4396 867.7792) 
(list 640.4396 867.7894) 
(list 640.4396 867.7997) 
(list 640.4396 867.81) 
(list 641.076 867.81)))
(apply 'command (append '("pline") coords '("c")))
(setq tap2 (ssadd (entlast) tap2))
(command "_mirror" (entlast) "" "640,900" "640,901" "No")
(setq tap2 (ssadd (entlast) tap2))
(setq coords (list 
(list 640 867.81) 
(list 640.135 867.81) 
(list 640.135 867.8203) 
(list 640.135 867.8306) 
(list 640.135 867.8408) 
(list 640.135 867.8511) 
(list 640.135 867.8614) 
(list 640.135 867.8717) 
(list 640.135 867.8819) 
(list 640.135 867.8922) 
(list 640.135 867.9025) 
(list 640.135 867.9128) 
(list 640.135 867.9231) 
(list 640.135 867.9333) 
(list 640.135 867.9436) 
(list 640.135 867.9539) 
(list 640.135 867.9642) 
(list 640.135 867.9744) 
(list 640.135 867.9847) 
(list 640.135 867.995) 
(list 640.135 868.0053) 
(list 640.135 868.0156) 
(list 640.135 868.0258) 
(list 640.135 868.0361) 
(list 640.135 868.0464) 
(list 640.135 868.0567) 
(list 640.135 868.0669) 
(list 640.135 868.0772) 
(list 640.135 868.0875) 
(list 640.135 868.0978) 
(list 640.135 868.1081) 
(list 640.135 868.1183) 
(list 640.135 868.1286) 
(list 640.135 868.1389) 
(list 640.135 868.1492) 
(list 640.135 868.1594) 
(list 640.135 868.1697) 
(list 640.135 868.18) 
(list 640 868.18)))
(apply 'command (append '("pline") coords '("c")))
(setq tap2 (ssadd (entlast) tap2))
(command "_mirror" (entlast) "" "640,900" "640,901" "No")
(setq tap2 (ssadd (entlast) tap2))
(setq coords (list 
(list 640.4478 867.81) 
(list 640.4396 867.81) 
(list 640.4394 867.8203) 
(list 640.4385 867.8306) 
(list 640.4368 867.8408) 
(list 640.4343 867.8511) 
(list 640.4312 867.8614) 
(list 640.4276 867.8717) 
(list 640.4234 867.8819) 
(list 640.4189 867.8922) 
(list 640.4141 867.9025) 
(list 640.4093 867.9128) 
(list 640.4045 867.9231) 
(list 640.4 867.9333) 
(list 640.3958 867.9436) 
(list 640.3921 867.9539) 
(list 640.389 867.9642) 
(list 640.3867 867.9744) 
(list 640.3851 867.9847) 
(list 640.3844 867.995) 
(list 640.3846 868.0053) 
(list 640.3858 868.0156) 
(list 640.3878 868.0258) 
(list 640.3906 868.0361) 
(list 640.3942 868.0464) 
(list 640.3985 868.0567) 
(list 640.4033 868.0669) 
(list 640.4085 868.0772) 
(list 640.414 868.0875) 
(list 640.4195 868.0978) 
(list 640.425 868.1081) 
(list 640.4302 868.1183) 
(list 640.435 868.1286) 
(list 640.4392 868.1389) 
(list 640.4427 868.1492) 
(list 640.4453 868.1594) 
(list 640.4471 868.1697) 
(list 640.4478 868.18) 
(list 640.4478 868.18)))
(apply 'command (append '("pline") coords '("c")))
(setq tap2 (ssadd (entlast) tap2))
(command "_mirror" (entlast) "" "640,900" "640,901" "No")
(setq tap2 (ssadd (entlast) tap2))
(setq coords (list 
(list 641.076 867.81) 
(list 640.4478 867.81) 
(list 640.4478 867.8203) 
(list 640.4478 867.8306) 
(list 640.4478 867.8408) 
(list 640.4478 867.8511) 
(list 640.4478 867.8614) 
(list 640.4478 867.8717) 
(list 640.4478 867.8819) 
(list 640.4478 867.8922) 
(list 640.4478 867.9025) 
(list 640.4478 867.9128) 
(list 640.4478 867.9231) 
(list 640.4478 867.9333) 
(list 640.4478 867.9436) 
(list 640.4478 867.9539) 
(list 640.4478 867.9642) 
(list 640.4478 867.9744) 
(list 640.4478 867.9847) 
(list 640.4478 867.995) 
(list 640.4478 868.0053) 
(list 640.4478 868.0156) 
(list 640.4478 868.0258) 
(list 640.4478 868.0361) 
(list 640.4478 868.0464) 
(list 640.4478 868.0567) 
(list 640.4478 868.0669) 
(list 640.4478 868.0772) 
(list 640.4478 868.0875) 
(list 640.4478 868.0978) 
(list 640.4478 868.1081) 
(list 640.4478 868.1183) 
(list 640.4478 868.1286) 
(list 640.4478 868.1389) 
(list 640.4478 868.1492) 
(list 640.4478 868.1594) 
(list 640.4478 868.1697) 
(list 640.4478 868.18) 
(list 641.076 868.18)))
(apply 'command (append '("pline") coords '("c")))
(setq tap2 (ssadd (entlast) tap2))
(command "_mirror" (entlast) "" "640,900" "640,901" "No")
(setq tap2 (ssadd (entlast) tap2))
(setq coords (list 
(list 640 868.18) 
(list 640.135 868.18) 
(list 640.135 868.1903) 
(list 640.135 868.2006) 
(list 640.135 868.2108) 
(list 640.135 868.2211) 
(list 640.135 868.2314) 
(list 640.135 868.2417) 
(list 640.135 868.2519) 
(list 640.135 868.2622) 
(list 640.135 868.2725) 
(list 640.135 868.2828) 
(list 640.135 868.2931) 
(list 640.135 868.3033) 
(list 640.135 868.3136) 
(list 640.135 868.3239) 
(list 640.135 868.3342) 
(list 640.135 868.3444) 
(list 640.135 868.3547) 
(list 640.135 868.365) 
(list 640.135 868.3753) 
(list 640.135 868.3856) 
(list 640.135 868.3958) 
(list 640.135 868.4061) 
(list 640.135 868.4164) 
(list 640.135 868.4267) 
(list 640.135 868.4369) 
(list 640.135 868.4472) 
(list 640.135 868.4575) 
(list 640.135 868.4678) 
(list 640.135 868.4781) 
(list 640.135 868.4883) 
(list 640.135 868.4986) 
(list 640.135 868.5089) 
(list 640.135 868.5192) 
(list 640.135 868.5294) 
(list 640.135 868.5397) 
(list 640.135 868.55) 
(list 640 868.55)))
(apply 'command (append '("pline") coords '("c")))
(setq tap2 (ssadd (entlast) tap2))
(command "_mirror" (entlast) "" "640,900" "640,901" "No")
(setq tap2 (ssadd (entlast) tap2))
(setq coords (list 
(list 640.456 868.18) 
(list 640.4478 868.18) 
(list 640.4475 868.1903) 
(list 640.4462 868.2006) 
(list 640.4439 868.2108) 
(list 640.4406 868.2211) 
(list 640.4364 868.2314) 
(list 640.4315 868.2417) 
(list 640.426 868.2519) 
(list 640.4201 868.2622) 
(list 640.4139 868.2725) 
(list 640.4076 868.2828) 
(list 640.4014 868.2931) 
(list 640.3955 868.3033) 
(list 640.3901 868.3136) 
(list 640.3854 868.3239) 
(list 640.3814 868.3342) 
(list 640.3785 868.3444) 
(list 640.3765 868.3547) 
(list 640.3757 868.365) 
(list 640.376 868.3753) 
(list 640.3775 868.3856) 
(list 640.3802 868.3958) 
(list 640.3839 868.4061) 
(list 640.3885 868.4164) 
(list 640.394 868.4267) 
(list 640.4002 868.4369) 
(list 640.4068 868.4472) 
(list 640.4137 868.4575) 
(list 640.4207 868.4678) 
(list 640.4276 868.4781) 
(list 640.4342 868.4883) 
(list 640.4402 868.4986) 
(list 640.4454 868.5089) 
(list 640.4497 868.5192) 
(list 640.453 868.5294) 
(list 640.4551 868.5397) 
(list 640.456 868.55) 
(list 640.456 868.55)))
(apply 'command (append '("pline") coords '("c")))
(setq tap2 (ssadd (entlast) tap2))
(command "_mirror" (entlast) "" "640,900" "640,901" "No")
(setq tap2 (ssadd (entlast) tap2))
(setq coords (list 
(list 641.076 868.18) 
(list 640.456 868.18) 
(list 640.456 868.1903) 
(list 640.456 868.2006) 
(list 640.456 868.2108) 
(list 640.456 868.2211) 
(list 640.456 868.2314) 
(list 640.456 868.2417) 
(list 640.456 868.2519) 
(list 640.456 868.2622) 
(list 640.456 868.2725) 
(list 640.456 868.2828) 
(list 640.456 868.2931) 
(list 640.456 868.3033) 
(list 640.456 868.3136) 
(list 640.456 868.3239) 
(list 640.456 868.3342) 
(list 640.456 868.3444) 
(list 640.456 868.3547) 
(list 640.456 868.365) 
(list 640.456 868.3753) 
(list 640.456 868.3856) 
(list 640.456 868.3958) 
(list 640.456 868.4061) 
(list 640.456 868.4164) 
(list 640.456 868.4267) 
(list 640.456 868.4369) 
(list 640.456 868.4472) 
(list 640.456 868.4575) 
(list 640.456 868.4678) 
(list 640.456 868.4781) 
(list 640.456 868.4883) 
(list 640.456 868.4986) 
(list 640.456 868.5089) 
(list 640.456 868.5192) 
(list 640.456 868.5294) 
(list 640.456 868.5397) 
(list 640.456 868.55) 
(list 641.076 868.55)))
(apply 'command (append '("pline") coords '("c")))
(setq tap2 (ssadd (entlast) tap2))
(command "_mirror" (entlast) "" "640,900" "640,901" "No")
(setq tap2 (ssadd (entlast) tap2))
(setq coords (list 
(list 640 868.55) 
(list 640.135 868.55) 
(list 640.135 868.5603) 
(list 640.135 868.5706) 
(list 640.135 868.5808) 
(list 640.135 868.5911) 
(list 640.135 868.6014) 
(list 640.135 868.6117) 
(list 640.135 868.6219) 
(list 640.135 868.6322) 
(list 640.135 868.6425) 
(list 640.135 868.6528) 
(list 640.135 868.6631) 
(list 640.135 868.6733) 
(list 640.135 868.6836) 
(list 640.135 868.6939) 
(list 640.135 868.7042) 
(list 640.135 868.7144) 
(list 640.135 868.7247) 
(list 640.135 868.735) 
(list 640.135 868.7453) 
(list 640.135 868.7556) 
(list 640.135 868.7658) 
(list 640.135 868.7761) 
(list 640.135 868.7864) 
(list 640.135 868.7967) 
(list 640.135 868.8069) 
(list 640.135 868.8172) 
(list 640.135 868.8275) 
(list 640.135 868.8378) 
(list 640.135 868.8481) 
(list 640.135 868.8583) 
(list 640.135 868.8686) 
(list 640.135 868.8789) 
(list 640.135 868.8892) 
(list 640.135 868.8994) 
(list 640.135 868.9097) 
(list 640.135 868.92) 
(list 640 868.92)))
(apply 'command (append '("pline") coords '("c")))
(setq tap2 (ssadd (entlast) tap2))
(command "_mirror" (entlast) "" "640,900" "640,901" "No")
(setq tap2 (ssadd (entlast) tap2))
(setq coords (list 
(list 640.4642 868.55) 
(list 640.456 868.55) 
(list 640.4556 868.5603) 
(list 640.4539 868.5706) 
(list 640.4509 868.5808) 
(list 640.4468 868.5911) 
(list 640.4416 868.6014) 
(list 640.4355 868.6117) 
(list 640.4287 868.6219) 
(list 640.4213 868.6322) 
(list 640.4136 868.6425) 
(list 640.4058 868.6528) 
(list 640.3982 868.6631) 
(list 640.391 868.6733) 
(list 640.3844 868.6836) 
(list 640.3786 868.6939) 
(list 640.3738 868.7042) 
(list 640.3702 868.7144) 
(list 640.3679 868.7247) 
(list 640.367 868.735) 
(list 640.3674 868.7453) 
(list 640.3693 868.7556) 
(list 640.3726 868.7658) 
(list 640.3771 868.7761) 
(list 640.3828 868.7864) 
(list 640.3895 868.7967) 
(list 640.397 868.8069) 
(list 640.4051 868.8172) 
(list 640.4135 868.8275) 
(list 640.422 868.8378) 
(list 640.4303 868.8481) 
(list 640.4381 868.8583) 
(list 640.4453 868.8686) 
(list 640.4516 868.8789) 
(list 640.4568 868.8892) 
(list 640.4607 868.8994) 
(list 640.4632 868.9097) 
(list 640.4642 868.92) 
(list 640.4642 868.92)))
(apply 'command (append '("pline") coords '("c")))
(setq tap2 (ssadd (entlast) tap2))
(command "_mirror" (entlast) "" "640,900" "640,901" "No")
(setq tap2 (ssadd (entlast) tap2))
(setq coords (list 
(list 641.076 868.55) 
(list 640.4642 868.55) 
(list 640.4642 868.5603) 
(list 640.4642 868.5706) 
(list 640.4642 868.5808) 
(list 640.4642 868.5911) 
(list 640.4642 868.6014) 
(list 640.4642 868.6117) 
(list 640.4642 868.6219) 
(list 640.4642 868.6322) 
(list 640.4642 868.6425) 
(list 640.4642 868.6528) 
(list 640.4642 868.6631) 
(list 640.4642 868.6733) 
(list 640.4642 868.6836) 
(list 640.4642 868.6939) 
(list 640.4642 868.7042) 
(list 640.4642 868.7144) 
(list 640.4642 868.7247) 
(list 640.4642 868.735) 
(list 640.4642 868.7453) 
(list 640.4642 868.7556) 
(list 640.4642 868.7658) 
(list 640.4642 868.7761) 
(list 640.4642 868.7864) 
(list 640.4642 868.7967) 
(list 640.4642 868.8069) 
(list 640.4642 868.8172) 
(list 640.4642 868.8275) 
(list 640.4642 868.8378) 
(list 640.4642 868.8481) 
(list 640.4642 868.8583) 
(list 640.4642 868.8686) 
(list 640.4642 868.8789) 
(list 640.4642 868.8892) 
(list 640.4642 868.8994) 
(list 640.4642 868.9097) 
(list 640.4642 868.92) 
(list 641.076 868.92)))
(apply 'command (append '("pline") coords '("c")))
(setq tap2 (ssadd (entlast) tap2))
(command "_mirror" (entlast) "" "640,900" "640,901" "No")
(setq tap2 (ssadd (entlast) tap2))
(setq coords (list 
(list 640 868.92) 
(list 640.135 868.92) 
(list 640.135 868.9303) 
(list 640.135 868.9406) 
(list 640.135 868.9508) 
(list 640.135 868.9611) 
(list 640.135 868.9714) 
(list 640.135 868.9817) 
(list 640.135 868.9919) 
(list 640.135 869.0022) 
(list 640.135 869.0125) 
(list 640.135 869.0228) 
(list 640.135 869.0331) 
(list 640.135 869.0433) 
(list 640.135 869.0536) 
(list 640.135 869.0639) 
(list 640.135 869.0742) 
(list 640.135 869.0844) 
(list 640.135 869.0947) 
(list 640.135 869.105) 
(list 640.135 869.1153) 
(list 640.135 869.1256) 
(list 640.135 869.1358) 
(list 640.135 869.1461) 
(list 640.135 869.1564) 
(list 640.135 869.1667) 
(list 640.135 869.1769) 
(list 640.135 869.1872) 
(list 640.135 869.1975) 
(list 640.135 869.2078) 
(list 640.135 869.2181) 
(list 640.135 869.2283) 
(list 640.135 869.2386) 
(list 640.135 869.2489) 
(list 640.135 869.2592) 
(list 640.135 869.2694) 
(list 640.135 869.2797) 
(list 640.135 869.29) 
(list 640 869.29)))
(apply 'command (append '("pline") coords '("c")))
(setq tap2 (ssadd (entlast) tap2))
(command "_mirror" (entlast) "" "640,900" "640,901" "No")
(setq tap2 (ssadd (entlast) tap2))
(setq coords (list 
(list 640.4724 868.92) 
(list 640.4642 868.92) 
(list 640.4637 868.9303) 
(list 640.4616 868.9406) 
(list 640.458 868.9508) 
(list 640.453 868.9611) 
(list 640.4468 868.9714) 
(list 640.4395 868.9817) 
(list 640.4313 868.9919) 
(list 640.4225 869.0022) 
(list 640.4133 869.0125) 
(list 640.4041 869.0228) 
(list 640.3951 869.0331) 
(list 640.3865 869.0433) 
(list 640.3787 869.0536) 
(list 640.3719 869.0639) 
(list 640.3662 869.0742) 
(list 640.362 869.0844) 
(list 640.3593 869.0947) 
(list 640.3582 869.105) 
(list 640.3588 869.1153) 
(list 640.3611 869.1256) 
(list 640.365 869.1358) 
(list 640.3704 869.1461) 
(list 640.3771 869.1564) 
(list 640.385 869.1667) 
(list 640.3938 869.1769) 
(list 640.4033 869.1872) 
(list 640.4132 869.1975) 
(list 640.4232 869.2078) 
(list 640.4329 869.2181) 
(list 640.4421 869.2283) 
(list 640.4505 869.2386) 
(list 640.4578 869.2489) 
(list 640.4639 869.2592) 
(list 640.4684 869.2694) 
(list 640.4713 869.2797) 
(list 640.4724 869.29) 
(list 640.4724 869.29)))
(apply 'command (append '("pline") coords '("c")))
(setq tap2 (ssadd (entlast) tap2))
(command "_mirror" (entlast) "" "640,900" "640,901" "No")
(setq tap2 (ssadd (entlast) tap2))
(setq coords (list 
(list 641.076 868.92) 
(list 640.4724 868.92) 
(list 640.4724 868.9303) 
(list 640.4724 868.9406) 
(list 640.4724 868.9508) 
(list 640.4724 868.9611) 
(list 640.4724 868.9714) 
(list 640.4724 868.9817) 
(list 640.4724 868.9919) 
(list 640.4724 869.0022) 
(list 640.4724 869.0125) 
(list 640.4724 869.0228) 
(list 640.4724 869.0331) 
(list 640.4724 869.0433) 
(list 640.4724 869.0536) 
(list 640.4724 869.0639) 
(list 640.4724 869.0742) 
(list 640.4724 869.0844) 
(list 640.4724 869.0947) 
(list 640.4724 869.105) 
(list 640.4724 869.1153) 
(list 640.4724 869.1256) 
(list 640.4724 869.1358) 
(list 640.4724 869.1461) 
(list 640.4724 869.1564) 
(list 640.4724 869.1667) 
(list 640.4724 869.1769) 
(list 640.4724 869.1872) 
(list 640.4724 869.1975) 
(list 640.4724 869.2078) 
(list 640.4724 869.2181) 
(list 640.4724 869.2283) 
(list 640.4724 869.2386) 
(list 640.4724 869.2489) 
(list 640.4724 869.2592) 
(list 640.4724 869.2694) 
(list 640.4724 869.2797) 
(list 640.4724 869.29) 
(list 641.076 869.29)))
(apply 'command (append '("pline") coords '("c")))
(setq tap2 (ssadd (entlast) tap2))
(command "_mirror" (entlast) "" "640,900" "640,901" "No")
(setq tap2 (ssadd (entlast) tap2))
(setq coords (list 
(list 640 869.29) 
(list 640.135 869.29) 
(list 640.135 869.3003) 
(list 640.135 869.3106) 
(list 640.135 869.3208) 
(list 640.135 869.3311) 
(list 640.135 869.3414) 
(list 640.135 869.3517) 
(list 640.135 869.3619) 
(list 640.135 869.3722) 
(list 640.135 869.3825) 
(list 640.135 869.3928) 
(list 640.135 869.4031) 
(list 640.135 869.4133) 
(list 640.135 869.4236) 
(list 640.135 869.4339) 
(list 640.135 869.4442) 
(list 640.135 869.4544) 
(list 640.135 869.4647) 
(list 640.135 869.475) 
(list 640.135 869.4853) 
(list 640.135 869.4956) 
(list 640.135 869.5058) 
(list 640.135 869.5161) 
(list 640.135 869.5264) 
(list 640.135 869.5367) 
(list 640.135 869.5469) 
(list 640.135 869.5572) 
(list 640.135 869.5675) 
(list 640.135 869.5778) 
(list 640.135 869.5881) 
(list 640.135 869.5983) 
(list 640.135 869.6086) 
(list 640.135 869.6189) 
(list 640.135 869.6292) 
(list 640.135 869.6394) 
(list 640.135 869.6497) 
(list 640.135 869.66) 
(list 640 869.66)))
(apply 'command (append '("pline") coords '("c")))
(setq tap2 (ssadd (entlast) tap2))
(command "_mirror" (entlast) "" "640,900" "640,901" "No")
(setq tap2 (ssadd (entlast) tap2))
(setq coords (list 
(list 640.4806 869.29) 
(list 640.4724 869.29) 
(list 640.4717 869.3003) 
(list 640.4693 869.3106) 
(list 640.465 869.3208) 
(list 640.4592 869.3311) 
(list 640.4519 869.3414) 
(list 640.4434 869.3517) 
(list 640.4339 869.3619) 
(list 640.4237 869.3722) 
(list 640.4131 869.3825) 
(list 640.4024 869.3928) 
(list 640.3919 869.4031) 
(list 640.382 869.4133) 
(list 640.373 869.4236) 
(list 640.3651 869.4339) 
(list 640.3586 869.4442) 
(list 640.3538 869.4544) 
(list 640.3507 869.4647) 
(list 640.3495 869.475) 
(list 640.3502 869.4853) 
(list 640.3529 869.4956) 
(list 640.3574 869.5058) 
(list 640.3636 869.5161) 
(list 640.3714 869.5264) 
(list 640.3805 869.5367) 
(list 640.3907 869.5469) 
(list 640.4016 869.5572) 
(list 640.4129 869.5675) 
(list 640.4244 869.5778) 
(list 640.4355 869.5881) 
(list 640.4461 869.5983) 
(list 640.4557 869.6086) 
(list 640.4641 869.6189) 
(list 640.4709 869.6292) 
(list 640.4761 869.6394) 
(list 640.4793 869.6497) 
(list 640.4806 869.66) 
(list 640.4806 869.66)))
(apply 'command (append '("pline") coords '("c")))
(setq tap2 (ssadd (entlast) tap2))
(command "_mirror" (entlast) "" "640,900" "640,901" "No")
(setq tap2 (ssadd (entlast) tap2))
(setq coords (list 
(list 641.076 869.29) 
(list 640.4806 869.29) 
(list 640.4806 869.3003) 
(list 640.4806 869.3106) 
(list 640.4806 869.3208) 
(list 640.4806 869.3311) 
(list 640.4806 869.3414) 
(list 640.4806 869.3517) 
(list 640.4806 869.3619) 
(list 640.4806 869.3722) 
(list 640.4806 869.3825) 
(list 640.4806 869.3928) 
(list 640.4806 869.4031) 
(list 640.4806 869.4133) 
(list 640.4806 869.4236) 
(list 640.4806 869.4339) 
(list 640.4806 869.4442) 
(list 640.4806 869.4544) 
(list 640.4806 869.4647) 
(list 640.4806 869.475) 
(list 640.4806 869.4853) 
(list 640.4806 869.4956) 
(list 640.4806 869.5058) 
(list 640.4806 869.5161) 
(list 640.4806 869.5264) 
(list 640.4806 869.5367) 
(list 640.4806 869.5469) 
(list 640.4806 869.5572) 
(list 640.4806 869.5675) 
(list 640.4806 869.5778) 
(list 640.4806 869.5881) 
(list 640.4806 869.5983) 
(list 640.4806 869.6086) 
(list 640.4806 869.6189) 
(list 640.4806 869.6292) 
(list 640.4806 869.6394) 
(list 640.4806 869.6497) 
(list 640.4806 869.66) 
(list 641.076 869.66)))
(apply 'command (append '("pline") coords '("c")))
(setq tap2 (ssadd (entlast) tap2))
(command "_mirror" (entlast) "" "640,900" "640,901" "No")
(setq tap2 (ssadd (entlast) tap2))
(setq coords (list 
(list 640 869.66) 
(list 640.135 869.66) 
(list 640.135 869.6703) 
(list 640.135 869.6806) 
(list 640.135 869.6908) 
(list 640.135 869.7011) 
(list 640.135 869.7114) 
(list 640.135 869.7217) 
(list 640.135 869.7319) 
(list 640.135 869.7422) 
(list 640.135 869.7525) 
(list 640.135 869.7628) 
(list 640.135 869.7731) 
(list 640.135 869.7833) 
(list 640.135 869.7936) 
(list 640.135 869.8039) 
(list 640.135 869.8142) 
(list 640.135 869.8244) 
(list 640.135 869.8347) 
(list 640.135 869.845) 
(list 640.135 869.8553) 
(list 640.135 869.8656) 
(list 640.135 869.8758) 
(list 640.135 869.8861) 
(list 640.135 869.8964) 
(list 640.135 869.9067) 
(list 640.135 869.9169) 
(list 640.135 869.9272) 
(list 640.135 869.9375) 
(list 640.135 869.9478) 
(list 640.135 869.9581) 
(list 640.135 869.9683) 
(list 640.135 869.9786) 
(list 640.135 869.9889) 
(list 640.135 869.9992) 
(list 640.135 870.0094) 
(list 640.135 870.0197) 
(list 640.135 870.03) 
(list 640 870.03)))
(apply 'command (append '("pline") coords '("c")))
(setq tap2 (ssadd (entlast) tap2))
(command "_mirror" (entlast) "" "640,900" "640,901" "No")
(setq tap2 (ssadd (entlast) tap2))
(setq coords (list 
(list 640.4888 869.66) 
(list 640.4806 869.66) 
(list 640.4798 869.6703) 
(list 640.4769 869.6806) 
(list 640.4721 869.6908) 
(list 640.4654 869.7011) 
(list 640.4571 869.7114) 
(list 640.4474 869.7217) 
(list 640.4365 869.7319) 
(list 640.4249 869.7422) 
(list 640.4128 869.7525) 
(list 640.4006 869.7628) 
(list 640.3887 869.7731) 
(list 640.3775 869.7833) 
(list 640.3673 869.7936) 
(list 640.3584 869.8039) 
(list 640.351 869.8142) 
(list 640.3456 869.8244) 
(list 640.3421 869.8347) 
(list 640.3408 869.845) 
(list 640.3416 869.8553) 
(list 640.3447 869.8656) 
(list 640.3498 869.8758) 
(list 640.3569 869.8861) 
(list 640.3657 869.8964) 
(list 640.376 869.9067) 
(list 640.3875 869.9169) 
(list 640.3999 869.9272) 
(list 640.4127 869.9375) 
(list 640.4256 869.9478) 
(list 640.4382 869.9581) 
(list 640.45 869.9683) 
(list 640.4609 869.9786) 
(list 640.4703 869.9889) 
(list 640.478 869.9992) 
(list 640.4838 870.0094) 
(list 640.4874 870.0197) 
(list 640.4888 870.03) 
(list 640.4888 870.03)))
(apply 'command (append '("pline") coords '("c")))
(setq tap2 (ssadd (entlast) tap2))
(command "_mirror" (entlast) "" "640,900" "640,901" "No")
(setq tap2 (ssadd (entlast) tap2))
(setq coords (list 
(list 641.076 869.66) 
(list 640.4888 869.66) 
(list 640.4888 869.6703) 
(list 640.4888 869.6806) 
(list 640.4888 869.6908) 
(list 640.4888 869.7011) 
(list 640.4888 869.7114) 
(list 640.4888 869.7217) 
(list 640.4888 869.7319) 
(list 640.4888 869.7422) 
(list 640.4888 869.7525) 
(list 640.4888 869.7628) 
(list 640.4888 869.7731) 
(list 640.4888 869.7833) 
(list 640.4888 869.7936) 
(list 640.4888 869.8039) 
(list 640.4888 869.8142) 
(list 640.4888 869.8244) 
(list 640.4888 869.8347) 
(list 640.4888 869.845) 
(list 640.4888 869.8553) 
(list 640.4888 869.8656) 
(list 640.4888 869.8758) 
(list 640.4888 869.8861) 
(list 640.4888 869.8964) 
(list 640.4888 869.9067) 
(list 640.4888 869.9169) 
(list 640.4888 869.9272) 
(list 640.4888 869.9375) 
(list 640.4888 869.9478) 
(list 640.4888 869.9581) 
(list 640.4888 869.9683) 
(list 640.4888 869.9786) 
(list 640.4888 869.9889) 
(list 640.4888 869.9992) 
(list 640.4888 870.0094) 
(list 640.4888 870.0197) 
(list 640.4888 870.03) 
(list 641.076 870.03)))
(apply 'command (append '("pline") coords '("c")))
(setq tap2 (ssadd (entlast) tap2))
(command "_mirror" (entlast) "" "640,900" "640,901" "No")
(setq tap2 (ssadd (entlast) tap2))
(setq coords (list 
(list 640 870.03) 
(list 640.135 870.03) 
(list 640.135 870.0403) 
(list 640.135 870.0506) 
(list 640.135 870.0608) 
(list 640.135 870.0711) 
(list 640.135 870.0814) 
(list 640.135 870.0917) 
(list 640.135 870.1019) 
(list 640.135 870.1122) 
(list 640.135 870.1225) 
(list 640.135 870.1328) 
(list 640.135 870.1431) 
(list 640.135 870.1533) 
(list 640.135 870.1636) 
(list 640.135 870.1739) 
(list 640.135 870.1842) 
(list 640.135 870.1944) 
(list 640.135 870.2047) 
(list 640.135 870.215) 
(list 640.135 870.2253) 
(list 640.135 870.2356) 
(list 640.135 870.2458) 
(list 640.135 870.2561) 
(list 640.135 870.2664) 
(list 640.135 870.2767) 
(list 640.135 870.2869) 
(list 640.135 870.2972) 
(list 640.135 870.3075) 
(list 640.135 870.3178) 
(list 640.135 870.3281) 
(list 640.135 870.3383) 
(list 640.135 870.3486) 
(list 640.135 870.3589) 
(list 640.135 870.3692) 
(list 640.135 870.3794) 
(list 640.135 870.3897) 
(list 640.135 870.4) 
(list 640 870.4)))
(apply 'command (append '("pline") coords '("c")))
(setq tap2 (ssadd (entlast) tap2))
(command "_mirror" (entlast) "" "640,900" "640,901" "No")
(setq tap2 (ssadd (entlast) tap2))
(setq coords (list 
(list 640.497 870.03) 
(list 640.4888 870.03) 
(list 640.4879 870.0403) 
(list 640.4846 870.0506) 
(list 640.4792 870.0608) 
(list 640.4717 870.0711) 
(list 640.4623 870.0814) 
(list 640.4514 870.0917) 
(list 640.4392 870.1019) 
(list 640.4261 870.1122) 
(list 640.4125 870.1225) 
(list 640.3989 870.1328) 
(list 640.3856 870.1431) 
(list 640.373 870.1533) 
(list 640.3616 870.1636) 
(list 640.3516 870.1739) 
(list 640.3434 870.1842) 
(list 640.3373 870.1944) 
(list 640.3335 870.2047) 
(list 640.332 870.215) 
(list 640.333 870.2253) 
(list 640.3364 870.2356) 
(list 640.3422 870.2458) 
(list 640.3501 870.2561) 
(list 640.36 870.2664) 
(list 640.3715 870.2767) 
(list 640.3843 870.2869) 
(list 640.3981 870.2972) 
(list 640.4124 870.3075) 
(list 640.4268 870.3178) 
(list 640.4408 870.3281) 
(list 640.454 870.3383) 
(list 640.466 870.3486) 
(list 640.4765 870.3589) 
(list 640.4851 870.3692) 
(list 640.4915 870.3794) 
(list 640.4955 870.3897) 
(list 640.497 870.4) 
(list 640.497 870.4)))
(apply 'command (append '("pline") coords '("c")))
(setq tap2 (ssadd (entlast) tap2))
(command "_mirror" (entlast) "" "640,900" "640,901" "No")
(setq tap2 (ssadd (entlast) tap2))
(setq coords (list 
(list 641.076 870.03) 
(list 640.497 870.03) 
(list 640.497 870.0403) 
(list 640.497 870.0506) 
(list 640.497 870.0608) 
(list 640.497 870.0711) 
(list 640.497 870.0814) 
(list 640.497 870.0917) 
(list 640.497 870.1019) 
(list 640.497 870.1122) 
(list 640.497 870.1225) 
(list 640.497 870.1328) 
(list 640.497 870.1431) 
(list 640.497 870.1533) 
(list 640.497 870.1636) 
(list 640.497 870.1739) 
(list 640.497 870.1842) 
(list 640.497 870.1944) 
(list 640.497 870.2047) 
(list 640.497 870.215) 
(list 640.497 870.2253) 
(list 640.497 870.2356) 
(list 640.497 870.2458) 
(list 640.497 870.2561) 
(list 640.497 870.2664) 
(list 640.497 870.2767) 
(list 640.497 870.2869) 
(list 640.497 870.2972) 
(list 640.497 870.3075) 
(list 640.497 870.3178) 
(list 640.497 870.3281) 
(list 640.497 870.3383) 
(list 640.497 870.3486) 
(list 640.497 870.3589) 
(list 640.497 870.3692) 
(list 640.497 870.3794) 
(list 640.497 870.3897) 
(list 640.497 870.4) 
(list 641.076 870.4)))
(apply 'command (append '("pline") coords '("c")))
(setq tap2 (ssadd (entlast) tap2))
(command "_mirror" (entlast) "" "640,900" "640,901" "No")
(setq tap2 (ssadd (entlast) tap2))
(setq coords (list 
(list 640 870.4) 
(list 640.135 870.4) 
(list 640.135 870.4103) 
(list 640.135 870.4206) 
(list 640.135 870.4308) 
(list 640.135 870.4411) 
(list 640.135 870.4514) 
(list 640.135 870.4617) 
(list 640.135 870.4719) 
(list 640.135 870.4822) 
(list 640.135 870.4925) 
(list 640.135 870.5028) 
(list 640.135 870.5131) 
(list 640.135 870.5233) 
(list 640.135 870.5336) 
(list 640.135 870.5439) 
(list 640.135 870.5542) 
(list 640.135 870.5644) 
(list 640.135 870.5747) 
(list 640.135 870.585) 
(list 640.135 870.5953) 
(list 640.135 870.6056) 
(list 640.135 870.6158) 
(list 640.135 870.6261) 
(list 640.135 870.6364) 
(list 640.135 870.6467) 
(list 640.135 870.6569) 
(list 640.135 870.6672) 
(list 640.135 870.6775) 
(list 640.135 870.6878) 
(list 640.135 870.6981) 
(list 640.135 870.7083) 
(list 640.135 870.7186) 
(list 640.135 870.7289) 
(list 640.135 870.7392) 
(list 640.135 870.7494) 
(list 640.135 870.7597) 
(list 640.135 870.77) 
(list 640 870.77)))
(apply 'command (append '("pline") coords '("c")))
(setq tap2 (ssadd (entlast) tap2))
(command "_mirror" (entlast) "" "640,900" "640,901" "No")
(setq tap2 (ssadd (entlast) tap2))
(setq coords (list 
(list 640.5052 870.4) 
(list 640.497 870.4) 
(list 640.4959 870.4103) 
(list 640.4923 870.4206) 
(list 640.4862 870.4308) 
(list 640.4779 870.4411) 
(list 640.4675 870.4514) 
(list 640.4553 870.4617) 
(list 640.4418 870.4719) 
(list 640.4273 870.4822) 
(list 640.4123 870.4925) 
(list 640.3971 870.5028) 
(list 640.3824 870.5131) 
(list 640.3685 870.5233) 
(list 640.3558 870.5336) 
(list 640.3448 870.5439) 
(list 640.3358 870.5542) 
(list 640.3291 870.5644) 
(list 640.3249 870.5747) 
(list 640.3233 870.585) 
(list 640.3244 870.5953) 
(list 640.3282 870.6056) 
(list 640.3346 870.6158) 
(list 640.3433 870.6261) 
(list 640.3543 870.6364) 
(list 640.367 870.6467) 
(list 640.3812 870.6569) 
(list 640.3964 870.6672) 
(list 640.4121 870.6775) 
(list 640.428 870.6878) 
(list 640.4434 870.6981) 
(list 640.458 870.7083) 
(list 640.4712 870.7186) 
(list 640.4827 870.7289) 
(list 640.4921 870.7392) 
(list 640.4992 870.7494) 
(list 640.5036 870.7597) 
(list 640.5052 870.77) 
(list 640.5052 870.77)))
(apply 'command (append '("pline") coords '("c")))
(setq tap2 (ssadd (entlast) tap2))
(command "_mirror" (entlast) "" "640,900" "640,901" "No")
(setq tap2 (ssadd (entlast) tap2))
(setq coords (list 
(list 641.076 870.4) 
(list 640.5052 870.4) 
(list 640.5052 870.4103) 
(list 640.5052 870.4206) 
(list 640.5052 870.4308) 
(list 640.5052 870.4411) 
(list 640.5052 870.4514) 
(list 640.5052 870.4617) 
(list 640.5052 870.4719) 
(list 640.5052 870.4822) 
(list 640.5052 870.4925) 
(list 640.5052 870.5028) 
(list 640.5052 870.5131) 
(list 640.5052 870.5233) 
(list 640.5052 870.5336) 
(list 640.5052 870.5439) 
(list 640.5052 870.5542) 
(list 640.5052 870.5644) 
(list 640.5052 870.5747) 
(list 640.5052 870.585) 
(list 640.5052 870.5953) 
(list 640.5052 870.6056) 
(list 640.5052 870.6158) 
(list 640.5052 870.6261) 
(list 640.5052 870.6364) 
(list 640.5052 870.6467) 
(list 640.5052 870.6569) 
(list 640.5052 870.6672) 
(list 640.5052 870.6775) 
(list 640.5052 870.6878) 
(list 640.5052 870.6981) 
(list 640.5052 870.7083) 
(list 640.5052 870.7186) 
(list 640.5052 870.7289) 
(list 640.5052 870.7392) 
(list 640.5052 870.7494) 
(list 640.5052 870.7597) 
(list 640.5052 870.77) 
(list 641.076 870.77)))
(apply 'command (append '("pline") coords '("c")))
(setq tap2 (ssadd (entlast) tap2))
(command "_mirror" (entlast) "" "640,900" "640,901" "No")
(setq tap2 (ssadd (entlast) tap2))
(setq coords (list 
(list 640 870.77) 
(list 640.135 870.77) 
(list 640.135 870.7803) 
(list 640.135 870.7906) 
(list 640.135 870.8008) 
(list 640.135 870.8111) 
(list 640.135 870.8214) 
(list 640.135 870.8317) 
(list 640.135 870.8419) 
(list 640.135 870.8522) 
(list 640.135 870.8625) 
(list 640.135 870.8728) 
(list 640.135 870.8831) 
(list 640.135 870.8933) 
(list 640.135 870.9036) 
(list 640.135 870.9139) 
(list 640.135 870.9242) 
(list 640.135 870.9344) 
(list 640.135 870.9447) 
(list 640.135 870.955) 
(list 640.135 870.9653) 
(list 640.135 870.9756) 
(list 640.135 870.9858) 
(list 640.135 870.9961) 
(list 640.135 871.0064) 
(list 640.135 871.0167) 
(list 640.135 871.0269) 
(list 640.135 871.0372) 
(list 640.135 871.0475) 
(list 640.135 871.0578) 
(list 640.135 871.0681) 
(list 640.135 871.0783) 
(list 640.135 871.0886) 
(list 640.135 871.0989) 
(list 640.135 871.1092) 
(list 640.135 871.1194) 
(list 640.135 871.1297) 
(list 640.135 871.14) 
(list 640 871.14)))
(apply 'command (append '("pline") coords '("c")))
(setq tap2 (ssadd (entlast) tap2))
(command "_mirror" (entlast) "" "640,900" "640,901" "No")
(setq tap2 (ssadd (entlast) tap2))
(setq coords (list 
(list 640.5134 870.77) 
(list 640.5052 870.77) 
(list 640.504 870.7803) 
(list 640.5 870.7906) 
(list 640.4933 870.8008) 
(list 640.4841 870.8111) 
(list 640.4727 870.8214) 
(list 640.4593 870.8317) 
(list 640.4444 870.8419) 
(list 640.4285 870.8522) 
(list 640.412 870.8625) 
(list 640.3954 870.8728) 
(list 640.3792 870.8831) 
(list 640.364 870.8933) 
(list 640.3501 870.9036) 
(list 640.3381 870.9139) 
(list 640.3282 870.9242) 
(list 640.3209 870.9344) 
(list 640.3163 870.9447) 
(list 640.3146 870.955) 
(list 640.3158 870.9653) 
(list 640.32 870.9756) 
(list 640.327 870.9858) 
(list 640.3366 870.9961) 
(list 640.3486 871.0064) 
(list 640.3625 871.0167) 
(list 640.378 871.0269) 
(list 640.3946 871.0372) 
(list 640.4119 871.0475) 
(list 640.4292 871.0578) 
(list 640.446 871.0681) 
(list 640.4619 871.0783) 
(list 640.4764 871.0886) 
(list 640.4889 871.0989) 
(list 640.4992 871.1092) 
(list 640.5068 871.1194) 
(list 640.5116 871.1297) 
(list 640.5134 871.14) 
(list 640.5134 871.14)))
(apply 'command (append '("pline") coords '("c")))
(setq tap2 (ssadd (entlast) tap2))
(command "_mirror" (entlast) "" "640,900" "640,901" "No")
(setq tap2 (ssadd (entlast) tap2))
(setq coords (list 
(list 641.076 870.77) 
(list 640.5134 870.77) 
(list 640.5134 870.7803) 
(list 640.5134 870.7906) 
(list 640.5134 870.8008) 
(list 640.5134 870.8111) 
(list 640.5134 870.8214) 
(list 640.5134 870.8317) 
(list 640.5134 870.8419) 
(list 640.5134 870.8522) 
(list 640.5134 870.8625) 
(list 640.5134 870.8728) 
(list 640.5134 870.8831) 
(list 640.5134 870.8933) 
(list 640.5134 870.9036) 
(list 640.5134 870.9139) 
(list 640.5134 870.9242) 
(list 640.5134 870.9344) 
(list 640.5134 870.9447) 
(list 640.5134 870.955) 
(list 640.5134 870.9653) 
(list 640.5134 870.9756) 
(list 640.5134 870.9858) 
(list 640.5134 870.9961) 
(list 640.5134 871.0064) 
(list 640.5134 871.0167) 
(list 640.5134 871.0269) 
(list 640.5134 871.0372) 
(list 640.5134 871.0475) 
(list 640.5134 871.0578) 
(list 640.5134 871.0681) 
(list 640.5134 871.0783) 
(list 640.5134 871.0886) 
(list 640.5134 871.0989) 
(list 640.5134 871.1092) 
(list 640.5134 871.1194) 
(list 640.5134 871.1297) 
(list 640.5134 871.14) 
(list 641.076 871.14)))
(apply 'command (append '("pline") coords '("c")))
(setq tap2 (ssadd (entlast) tap2))
(command "_mirror" (entlast) "" "640,900" "640,901" "No")
(setq tap2 (ssadd (entlast) tap2))
(setq coords (list 
(list 640 871.14) 
(list 640.135 871.14) 
(list 640.135 871.1503) 
(list 640.135 871.1606) 
(list 640.135 871.1708) 
(list 640.135 871.1811) 
(list 640.135 871.1914) 
(list 640.135 871.2017) 
(list 640.135 871.2119) 
(list 640.135 871.2222) 
(list 640.135 871.2325) 
(list 640.135 871.2428) 
(list 640.135 871.2531) 
(list 640.135 871.2633) 
(list 640.135 871.2736) 
(list 640.135 871.2839) 
(list 640.135 871.2942) 
(list 640.135 871.3044) 
(list 640.135 871.3147) 
(list 640.135 871.325) 
(list 640.135 871.3353) 
(list 640.135 871.3456) 
(list 640.135 871.3558) 
(list 640.135 871.3661) 
(list 640.135 871.3764) 
(list 640.135 871.3867) 
(list 640.135 871.3969) 
(list 640.135 871.4072) 
(list 640.135 871.4175) 
(list 640.135 871.4278) 
(list 640.135 871.4381) 
(list 640.135 871.4483) 
(list 640.135 871.4586) 
(list 640.135 871.4689) 
(list 640.135 871.4792) 
(list 640.135 871.4894) 
(list 640.135 871.4997) 
(list 640.135 871.51) 
(list 640 871.51)))
(apply 'command (append '("pline") coords '("c")))
(setq tap2 (ssadd (entlast) tap2))
(command "_mirror" (entlast) "" "640,900" "640,901" "No")
(setq tap2 (ssadd (entlast) tap2))
(setq coords (list 
(list 640.5216 871.14) 
(list 640.5134 871.14) 
(list 640.5121 871.1503) 
(list 640.5077 871.1606) 
(list 640.5004 871.1708) 
(list 640.4903 871.1811) 
(list 640.4778 871.1914) 
(list 640.4633 871.2017) 
(list 640.4471 871.2119) 
(list 640.4297 871.2222) 
(list 640.4117 871.2325) 
(list 640.3937 871.2428) 
(list 640.3761 871.2531) 
(list 640.3595 871.2633) 
(list 640.3444 871.2736) 
(list 640.3313 871.2839) 
(list 640.3206 871.2942) 
(list 640.3127 871.3044) 
(list 640.3077 871.3147) 
(list 640.3058 871.325) 
(list 640.3072 871.3353) 
(list 640.3118 871.3456) 
(list 640.3194 871.3558) 
(list 640.3298 871.3661) 
(list 640.3428 871.3764) 
(list 640.358 871.3867) 
(list 640.3749 871.3969) 
(list 640.3929 871.4072) 
(list 640.4116 871.4175) 
(list 640.4304 871.4278) 
(list 640.4487 871.4381) 
(list 640.4659 871.4483) 
(list 640.4816 871.4586) 
(list 640.4952 871.4689) 
(list 640.5063 871.4792) 
(list 640.5145 871.4894) 
(list 640.5197 871.4997) 
(list 640.5216 871.51) 
(list 640.5216 871.51)))
(apply 'command (append '("pline") coords '("c")))
(setq tap2 (ssadd (entlast) tap2))
(command "_mirror" (entlast) "" "640,900" "640,901" "No")
(setq tap2 (ssadd (entlast) tap2))
(setq coords (list 
(list 641.076 871.14) 
(list 640.5216 871.14) 
(list 640.5216 871.1503) 
(list 640.5216 871.1606) 
(list 640.5216 871.1708) 
(list 640.5216 871.1811) 
(list 640.5216 871.1914) 
(list 640.5216 871.2017) 
(list 640.5216 871.2119) 
(list 640.5216 871.2222) 
(list 640.5216 871.2325) 
(list 640.5216 871.2428) 
(list 640.5216 871.2531) 
(list 640.5216 871.2633) 
(list 640.5216 871.2736) 
(list 640.5216 871.2839) 
(list 640.5216 871.2942) 
(list 640.5216 871.3044) 
(list 640.5216 871.3147) 
(list 640.5216 871.325) 
(list 640.5216 871.3353) 
(list 640.5216 871.3456) 
(list 640.5216 871.3558) 
(list 640.5216 871.3661) 
(list 640.5216 871.3764) 
(list 640.5216 871.3867) 
(list 640.5216 871.3969) 
(list 640.5216 871.4072) 
(list 640.5216 871.4175) 
(list 640.5216 871.4278) 
(list 640.5216 871.4381) 
(list 640.5216 871.4483) 
(list 640.5216 871.4586) 
(list 640.5216 871.4689) 
(list 640.5216 871.4792) 
(list 640.5216 871.4894) 
(list 640.5216 871.4997) 
(list 640.5216 871.51) 
(list 641.076 871.51)))
(apply 'command (append '("pline") coords '("c")))
(setq tap2 (ssadd (entlast) tap2))
(command "_mirror" (entlast) "" "640,900" "640,901" "No")
(setq tap2 (ssadd (entlast) tap2))
(setq coords (list 
(list 640 871.51) 
(list 640.135 871.51) 
(list 640.135 871.5203) 
(list 640.135 871.5306) 
(list 640.135 871.5408) 
(list 640.135 871.5511) 
(list 640.135 871.5614) 
(list 640.135 871.5717) 
(list 640.135 871.5819) 
(list 640.135 871.5922) 
(list 640.135 871.6025) 
(list 640.135 871.6128) 
(list 640.135 871.6231) 
(list 640.135 871.6333) 
(list 640.135 871.6436) 
(list 640.135 871.6539) 
(list 640.135 871.6642) 
(list 640.135 871.6744) 
(list 640.135 871.6847) 
(list 640.135 871.695) 
(list 640.135 871.7053) 
(list 640.135 871.7156) 
(list 640.135 871.7258) 
(list 640.135 871.7361) 
(list 640.135 871.7464) 
(list 640.135 871.7567) 
(list 640.135 871.7669) 
(list 640.135 871.7772) 
(list 640.135 871.7875) 
(list 640.135 871.7978) 
(list 640.135 871.8081) 
(list 640.135 871.8183) 
(list 640.135 871.8286) 
(list 640.135 871.8389) 
(list 640.135 871.8492) 
(list 640.135 871.8594) 
(list 640.135 871.8697) 
(list 640.135 871.88) 
(list 640 871.88)))
(apply 'command (append '("pline") coords '("c")))
(setq tap2 (ssadd (entlast) tap2))
(command "_mirror" (entlast) "" "640,900" "640,901" "No")
(setq tap2 (ssadd (entlast) tap2))
(setq coords (list 
(list 640.5298 871.51) 
(list 640.5216 871.51) 
(list 640.5202 871.5203) 
(list 640.5154 871.5306) 
(list 640.5074 871.5408) 
(list 640.4965 871.5511) 
(list 640.483 871.5614) 
(list 640.4672 871.5717) 
(list 640.4497 871.5819) 
(list 640.4309 871.5922) 
(list 640.4115 871.6025) 
(list 640.3919 871.6128) 
(list 640.3729 871.6231) 
(list 640.355 871.6333) 
(list 640.3387 871.6436) 
(list 640.3246 871.6539) 
(list 640.313 871.6642) 
(list 640.3044 871.6744) 
(list 640.2991 871.6847) 
(list 640.2971 871.695) 
(list 640.2986 871.7053) 
(list 640.3035 871.7156) 
(list 640.3118 871.7258) 
(list 640.3231 871.7361) 
(list 640.3371 871.7464) 
(list 640.3535 871.7567) 
(list 640.3717 871.7669) 
(list 640.3912 871.7772) 
(list 640.4113 871.7875) 
(list 640.4316 871.7978) 
(list 640.4513 871.8081) 
(list 640.4699 871.8183) 
(list 640.4867 871.8286) 
(list 640.5014 871.8389) 
(list 640.5133 871.8492) 
(list 640.5222 871.8594) 
(list 640.5278 871.8697) 
(list 640.5298 871.88) 
(list 640.5298 871.88)))
(apply 'command (append '("pline") coords '("c")))
(setq tap2 (ssadd (entlast) tap2))
(command "_mirror" (entlast) "" "640,900" "640,901" "No")
(setq tap2 (ssadd (entlast) tap2))
(setq coords (list 
(list 641.076 871.51) 
(list 640.5298 871.51) 
(list 640.5298 871.5203) 
(list 640.5298 871.5306) 
(list 640.5298 871.5408) 
(list 640.5298 871.5511) 
(list 640.5298 871.5614) 
(list 640.5298 871.5717) 
(list 640.5298 871.5819) 
(list 640.5298 871.5922) 
(list 640.5298 871.6025) 
(list 640.5298 871.6128) 
(list 640.5298 871.6231) 
(list 640.5298 871.6333) 
(list 640.5298 871.6436) 
(list 640.5298 871.6539) 
(list 640.5298 871.6642) 
(list 640.5298 871.6744) 
(list 640.5298 871.6847) 
(list 640.5298 871.695) 
(list 640.5298 871.7053) 
(list 640.5298 871.7156) 
(list 640.5298 871.7258) 
(list 640.5298 871.7361) 
(list 640.5298 871.7464) 
(list 640.5298 871.7567) 
(list 640.5298 871.7669) 
(list 640.5298 871.7772) 
(list 640.5298 871.7875) 
(list 640.5298 871.7978) 
(list 640.5298 871.8081) 
(list 640.5298 871.8183) 
(list 640.5298 871.8286) 
(list 640.5298 871.8389) 
(list 640.5298 871.8492) 
(list 640.5298 871.8594) 
(list 640.5298 871.8697) 
(list 640.5298 871.88) 
(list 641.076 871.88)))
(apply 'command (append '("pline") coords '("c")))
(setq tap2 (ssadd (entlast) tap2))
(command "_mirror" (entlast) "" "640,900" "640,901" "No")
(setq tap2 (ssadd (entlast) tap2))
(setq coords (list 
(list 640 871.88) 
(list 640.135 871.88) 
(list 640.135 871.8903) 
(list 640.135 871.9006) 
(list 640.135 871.9108) 
(list 640.135 871.9211) 
(list 640.135 871.9314) 
(list 640.135 871.9417) 
(list 640.135 871.9519) 
(list 640.135 871.9622) 
(list 640.135 871.9725) 
(list 640.135 871.9828) 
(list 640.135 871.9931) 
(list 640.135 872.0033) 
(list 640.135 872.0136) 
(list 640.135 872.0239) 
(list 640.135 872.0342) 
(list 640.135 872.0444) 
(list 640.135 872.0547) 
(list 640.135 872.065) 
(list 640.135 872.0753) 
(list 640.135 872.0856) 
(list 640.135 872.0958) 
(list 640.135 872.1061) 
(list 640.135 872.1164) 
(list 640.135 872.1267) 
(list 640.135 872.1369) 
(list 640.135 872.1472) 
(list 640.135 872.1575) 
(list 640.135 872.1678) 
(list 640.135 872.1781) 
(list 640.135 872.1883) 
(list 640.135 872.1986) 
(list 640.135 872.2089) 
(list 640.135 872.2192) 
(list 640.135 872.2294) 
(list 640.135 872.2397) 
(list 640.135 872.25) 
(list 640 872.25)))
(apply 'command (append '("pline") coords '("c")))
(setq tap2 (ssadd (entlast) tap2))
(command "_mirror" (entlast) "" "640,900" "640,901" "No")
(setq tap2 (ssadd (entlast) tap2))
(setq coords (list 
(list 640.538 871.88) 
(list 640.5298 871.88) 
(list 640.5282 871.8903) 
(list 640.5231 871.9006) 
(list 640.5145 871.9108) 
(list 640.5028 871.9211) 
(list 640.4882 871.9314) 
(list 640.4712 871.9417) 
(list 640.4523 871.9519) 
(list 640.4321 871.9622) 
(list 640.4112 871.9725) 
(list 640.3902 871.9828) 
(list 640.3698 871.9931) 
(list 640.3505 872.0033) 
(list 640.333 872.0136) 
(list 640.3178 872.0239) 
(list 640.3054 872.0342) 
(list 640.2962 872.0444) 
(list 640.2905 872.0547) 
(list 640.2884 872.065) 
(list 640.29 872.0753) 
(list 640.2953 872.0856) 
(list 640.3042 872.0958) 
(list 640.3163 872.1061) 
(list 640.3314 872.1164) 
(list 640.349 872.1267) 
(list 640.3685 872.1369) 
(list 640.3894 872.1472) 
(list 640.4111 872.1575) 
(list 640.4328 872.1678) 
(list 640.4539 872.1781) 
(list 640.4738 872.1883) 
(list 640.4919 872.1986) 
(list 640.5076 872.2089) 
(list 640.5204 872.2192) 
(list 640.5299 872.2294) 
(list 640.5358 872.2397) 
(list 640.538 872.25) 
(list 640.538 872.25)))
(apply 'command (append '("pline") coords '("c")))
(setq tap2 (ssadd (entlast) tap2))
(command "_mirror" (entlast) "" "640,900" "640,901" "No")
(setq tap2 (ssadd (entlast) tap2))
(setq coords (list 
(list 641.076 871.88) 
(list 640.538 871.88) 
(list 640.538 871.8903) 
(list 640.538 871.9006) 
(list 640.538 871.9108) 
(list 640.538 871.9211) 
(list 640.538 871.9314) 
(list 640.538 871.9417) 
(list 640.538 871.9519) 
(list 640.538 871.9622) 
(list 640.538 871.9725) 
(list 640.538 871.9828) 
(list 640.538 871.9931) 
(list 640.538 872.0033) 
(list 640.538 872.0136) 
(list 640.538 872.0239) 
(list 640.538 872.0342) 
(list 640.538 872.0444) 
(list 640.538 872.0547) 
(list 640.538 872.065) 
(list 640.538 872.0753) 
(list 640.538 872.0856) 
(list 640.538 872.0958) 
(list 640.538 872.1061) 
(list 640.538 872.1164) 
(list 640.538 872.1267) 
(list 640.538 872.1369) 
(list 640.538 872.1472) 
(list 640.538 872.1575) 
(list 640.538 872.1678) 
(list 640.538 872.1781) 
(list 640.538 872.1883) 
(list 640.538 872.1986) 
(list 640.538 872.2089) 
(list 640.538 872.2192) 
(list 640.538 872.2294) 
(list 640.538 872.2397) 
(list 640.538 872.25) 
(list 641.076 872.25)))
(apply 'command (append '("pline") coords '("c")))
(setq tap2 (ssadd (entlast) tap2))
(command "_mirror" (entlast) "" "640,900" "640,901" "No")
(setq tap2 (ssadd (entlast) tap2))
(command "_block" "blktap2" "640,900" tap2 "")
(command "_insert" "blktap2" "640,900" "1" "1" "0")
(command "_insert" "blktap2" "640,900" "1" "1" "180")
(setq uc2 nil)
(setq uc2 (ssadd))
(setq coords (list 
(list 0 -0.185) 
(list 0.135 -0.185) 
(list 0.135 -0.17472) 
(list 0.135 -0.16444) 
(list 0.135 -0.15417) 
(list 0.135 -0.14389) 
(list 0.135 -0.13361) 
(list 0.135 -0.12333) 
(list 0.135 -0.11306) 
(list 0.135 -0.10278) 
(list 0.135 -0.0925) 
(list 0.135 -0.082222) 
(list 0.135 -0.071944) 
(list 0.135 -0.061667) 
(list 0.135 -0.051389) 
(list 0.135 -0.041111) 
(list 0.135 -0.030833) 
(list 0.135 -0.020556) 
(list 0.135 -0.010278) 
(list 0.135 0) 
(list 0.135 0.010278) 
(list 0.135 0.020556) 
(list 0.135 0.030833) 
(list 0.135 0.041111) 
(list 0.135 0.051389) 
(list 0.135 0.061667) 
(list 0.135 0.071944) 
(list 0.135 0.082222) 
(list 0.135 0.0925) 
(list 0.135 0.10278) 
(list 0.135 0.11306) 
(list 0.135 0.12333) 
(list 0.135 0.13361) 
(list 0.135 0.14389) 
(list 0.135 0.15417) 
(list 0.135 0.16444) 
(list 0.135 0.17472) 
(list 0.135 0.185) 
(list 0 0.185)))
(apply 'command (append '("pline") coords '("c")))
(setq uc2 (ssadd (entlast) uc2))
(setq coords (list 
(list 1.076 -0.185) 
(list 0.538 -0.185) 
(list 0.53607 -0.17472) 
(list 0.53034 -0.16444) 
(list 0.52099 -0.15417) 
(list 0.50829 -0.14389) 
(list 0.49263 -0.13361) 
(list 0.4745 -0.12333) 
(list 0.45444 -0.11306) 
(list 0.43305 -0.10278) 
(list 0.411 -0.0925) 
(list 0.38895 -0.082222) 
(list 0.36756 -0.071944) 
(list 0.3475 -0.061667) 
(list 0.32937 -0.051389) 
(list 0.31371 -0.041111) 
(list 0.30101 -0.030833) 
(list 0.29166 -0.020556) 
(list 0.28593 -0.010278) 
(list 0.284 0) 
(list 0.28593 0.010278) 
(list 0.29166 0.020556) 
(list 0.30101 0.030833) 
(list 0.31371 0.041111) 
(list 0.32937 0.051389) 
(list 0.3475 0.061667) 
(list 0.36756 0.071944) 
(list 0.38895 0.082222) 
(list 0.411 0.0925) 
(list 0.43305 0.10278) 
(list 0.45444 0.11306) 
(list 0.4745 0.12333) 
(list 0.49263 0.13361) 
(list 0.50829 0.14389) 
(list 0.52099 0.15417) 
(list 0.53034 0.16444) 
(list 0.53607 0.17472) 
(list 0.538 0.185) 
(list 1.076 0.185)))
(apply 'command (append '("pline") coords '("c")))
(setq uc2 (ssadd (entlast) uc2))
(command "_block" "blkuc2" "0,0.185" uc2 "")
(command "_insert" "blkuc2" "640,872.62" "1" "1" "0")
(command "_insert" "blkuc2" "640,872.25" "1" "1" "180")
(command "_insert" "blkuc2" "640,872.99" "1" "1" "0")
(command "_insert" "blkuc2" "640,872.62" "1" "1" "180")
(command "_insert" "blkuc2" "640,873.36" "1" "1" "0")
(command "_insert" "blkuc2" "640,872.99" "1" "1" "180")
(command "_insert" "blkuc2" "640,873.73" "1" "1" "0")
(command "_insert" "blkuc2" "640,873.36" "1" "1" "180")
(command "_insert" "blkuc2" "640,874.1" "1" "1" "0")
(command "_insert" "blkuc2" "640,873.73" "1" "1" "180")
(command "_insert" "blkuc2" "640,874.47" "1" "1" "0")
(command "_insert" "blkuc2" "640,874.1" "1" "1" "180")
(command "_insert" "blkuc2" "640,874.84" "1" "1" "0")
(command "_insert" "blkuc2" "640,874.47" "1" "1" "180")
(command "_insert" "blkuc2" "640,875.21" "1" "1" "0")
(command "_insert" "blkuc2" "640,874.84" "1" "1" "180")
(command "_insert" "blkuc2" "640,875.58" "1" "1" "0")
(command "_insert" "blkuc2" "640,875.21" "1" "1" "180")
(command "_insert" "blkuc2" "640,875.95" "1" "1" "0")
(command "_insert" "blkuc2" "640,875.58" "1" "1" "180")
(command "_insert" "blkuc2" "640,876.32" "1" "1" "0")
(command "_insert" "blkuc2" "640,875.95" "1" "1" "180")
(command "_insert" "blkuc2" "640,876.69" "1" "1" "0")
(command "_insert" "blkuc2" "640,876.32" "1" "1" "180")
(command "_insert" "blkuc2" "640,877.06" "1" "1" "0")
(command "_insert" "blkuc2" "640,876.69" "1" "1" "180")
(command "_insert" "blkuc2" "640,877.43" "1" "1" "0")
(command "_insert" "blkuc2" "640,877.06" "1" "1" "180")
(command "_insert" "blkuc2" "640,877.8" "1" "1" "0")
(command "_insert" "blkuc2" "640,877.43" "1" "1" "180")
(command "_insert" "blkuc2" "640,878.17" "1" "1" "0")
(command "_insert" "blkuc2" "640,877.8" "1" "1" "180")
(command "_insert" "blkuc2" "640,878.54" "1" "1" "0")
(command "_insert" "blkuc2" "640,878.17" "1" "1" "180")
(command "_insert" "blkuc2" "640,878.91" "1" "1" "0")
(command "_insert" "blkuc2" "640,878.54" "1" "1" "180")
(command "_insert" "blkuc2" "640,879.28" "1" "1" "0")
(command "_insert" "blkuc2" "640,878.91" "1" "1" "180")
(command "_insert" "blkuc2" "640,879.65" "1" "1" "0")
(command "_insert" "blkuc2" "640,879.28" "1" "1" "180")
(command "_insert" "blkuc2" "640,880.02" "1" "1" "0")
(command "_insert" "blkuc2" "640,879.65" "1" "1" "180")
(command "_insert" "blkuc2" "640,880.39" "1" "1" "0")
(command "_insert" "blkuc2" "640,880.02" "1" "1" "180")
(command "_insert" "blkuc2" "640,880.76" "1" "1" "0")
(command "_insert" "blkuc2" "640,880.39" "1" "1" "180")
(command "_insert" "blkuc2" "640,881.13" "1" "1" "0")
(command "_insert" "blkuc2" "640,880.76" "1" "1" "180")
(command "_insert" "blkuc2" "640,881.5" "1" "1" "0")
(command "_insert" "blkuc2" "640,881.13" "1" "1" "180")
(command "_insert" "blkuc2" "640,881.87" "1" "1" "0")
(command "_insert" "blkuc2" "640,881.5" "1" "1" "180")
(command "_insert" "blkuc2" "640,882.24" "1" "1" "0")
(command "_insert" "blkuc2" "640,881.87" "1" "1" "180")
(command "_insert" "blkuc2" "640,882.61" "1" "1" "0")
(command "_insert" "blkuc2" "640,882.24" "1" "1" "180")
(command "_insert" "blkuc2" "640,882.98" "1" "1" "0")
(command "_insert" "blkuc2" "640,882.61" "1" "1" "180")
(command "_insert" "blkuc2" "640,883.35" "1" "1" "0")
(command "_insert" "blkuc2" "640,882.98" "1" "1" "180")
(command "_insert" "blkuc2" "640,883.72" "1" "1" "0")
(command "_insert" "blkuc2" "640,883.35" "1" "1" "180")
(command "_insert" "blkuc2" "640,884.09" "1" "1" "0")
(command "_insert" "blkuc2" "640,883.72" "1" "1" "180")
(command "_insert" "blkuc2" "640,884.46" "1" "1" "0")
(command "_insert" "blkuc2" "640,884.09" "1" "1" "180")
(command "_insert" "blkuc2" "640,884.83" "1" "1" "0")
(command "_insert" "blkuc2" "640,884.46" "1" "1" "180")
(command "_insert" "blkuc2" "640,885.2" "1" "1" "0")
(command "_insert" "blkuc2" "640,884.83" "1" "1" "180")
(command "_insert" "blkuc2" "640,885.57" "1" "1" "0")
(command "_insert" "blkuc2" "640,885.2" "1" "1" "180")
(command "_insert" "blkuc2" "640,885.94" "1" "1" "0")
(command "_insert" "blkuc2" "640,885.57" "1" "1" "180")
(command "_insert" "blkuc2" "640,886.31" "1" "1" "0")
(command "_insert" "blkuc2" "640,885.94" "1" "1" "180")
(command "_insert" "blkuc2" "640,886.68" "1" "1" "0")
(command "_insert" "blkuc2" "640,886.31" "1" "1" "180")
(command "_insert" "blkuc2" "640,887.05" "1" "1" "0")
(command "_insert" "blkuc2" "640,886.68" "1" "1" "180")
(command "_insert" "blkuc2" "640,887.42" "1" "1" "0")
(command "_insert" "blkuc2" "640,887.05" "1" "1" "180")
(command "_insert" "blkuc2" "640,887.79" "1" "1" "0")
(command "_insert" "blkuc2" "640,887.42" "1" "1" "180")
(command "_insert" "blkuc2" "640,888.16" "1" "1" "0")
(command "_insert" "blkuc2" "640,887.79" "1" "1" "180")
(command "_insert" "blkuc2" "640,888.53" "1" "1" "0")
(command "_insert" "blkuc2" "640,888.16" "1" "1" "180")
(command "_insert" "blkuc2" "640,888.9" "1" "1" "0")
(command "_insert" "blkuc2" "640,888.53" "1" "1" "180")
(command "_insert" "blkuc2" "640,889.27" "1" "1" "0")
(command "_insert" "blkuc2" "640,888.9" "1" "1" "180")
(command "_insert" "blkuc2" "640,889.64" "1" "1" "0")
(command "_insert" "blkuc2" "640,889.27" "1" "1" "180")
(command "_insert" "blkuc2" "640,890.01" "1" "1" "0")
(command "_insert" "blkuc2" "640,889.64" "1" "1" "180")
(command "_insert" "blkuc2" "640,890.38" "1" "1" "0")
(command "_insert" "blkuc2" "640,890.01" "1" "1" "180")
(command "_insert" "blkuc2" "640,890.75" "1" "1" "0")
(command "_insert" "blkuc2" "640,890.38" "1" "1" "180")
(command "_insert" "blkuc2" "640,891.12" "1" "1" "0")
(command "_insert" "blkuc2" "640,890.75" "1" "1" "180")
(command "_insert" "blkuc2" "640,891.49" "1" "1" "0")
(command "_insert" "blkuc2" "640,891.12" "1" "1" "180")
(command "_insert" "blkuc2" "640,891.86" "1" "1" "0")
(command "_insert" "blkuc2" "640,891.49" "1" "1" "180")
(command "_insert" "blkuc2" "640,892.23" "1" "1" "0")
(command "_insert" "blkuc2" "640,891.86" "1" "1" "180")
(command "_insert" "blkuc2" "640,892.6" "1" "1" "0")
(command "_insert" "blkuc2" "640,892.23" "1" "1" "180")
(command "_insert" "blkuc2" "640,892.97" "1" "1" "0")
(command "_insert" "blkuc2" "640,892.6" "1" "1" "180")
(command "_insert" "blkuc2" "640,893.34" "1" "1" "0")
(command "_insert" "blkuc2" "640,892.97" "1" "1" "180")
(command "_insert" "blkuc2" "640,893.71" "1" "1" "0")
(command "_insert" "blkuc2" "640,893.34" "1" "1" "180")
(command "_insert" "blkuc2" "640,894.08" "1" "1" "0")
(command "_insert" "blkuc2" "640,893.71" "1" "1" "180")
(command "_insert" "blkuc2" "640,894.45" "1" "1" "0")
(command "_insert" "blkuc2" "640,894.08" "1" "1" "180")
(command "_insert" "blkuc2" "640,894.82" "1" "1" "0")
(command "_insert" "blkuc2" "640,894.45" "1" "1" "180")
(command "_insert" "blkuc2" "640,895.19" "1" "1" "0")
(command "_insert" "blkuc2" "640,894.82" "1" "1" "180")
(command "_insert" "blkuc2" "640,895.56" "1" "1" "0")
(command "_insert" "blkuc2" "640,895.19" "1" "1" "180")
(command "_insert" "blkuc2" "640,895.93" "1" "1" "0")
(command "_insert" "blkuc2" "640,895.56" "1" "1" "180")
(command "_insert" "blkuc2" "640,896.3" "1" "1" "0")
(command "_insert" "blkuc2" "640,895.93" "1" "1" "180")
(command "_insert" "blkuc2" "640,896.67" "1" "1" "0")
(command "_insert" "blkuc2" "640,896.3" "1" "1" "180")
(command "_insert" "blkuc2" "640,897.04" "1" "1" "0")
(command "_insert" "blkuc2" "640,896.67" "1" "1" "180")
(command "_insert" "blkuc2" "640,897.41" "1" "1" "0")
(command "_insert" "blkuc2" "640,897.04" "1" "1" "180")
(command "_insert" "blkuc2" "640,897.78" "1" "1" "0")
(command "_insert" "blkuc2" "640,897.41" "1" "1" "180")
(command "_insert" "blkuc2" "640,898.15" "1" "1" "0")
(command "_insert" "blkuc2" "640,897.78" "1" "1" "180")
(command "_insert" "blkuc2" "640,898.52" "1" "1" "0")
(command "_insert" "blkuc2" "640,898.15" "1" "1" "180")
(command "_insert" "blkuc2" "640,898.89" "1" "1" "0")
(command "_insert" "blkuc2" "640,898.52" "1" "1" "180")
(command "_insert" "blkuc2" "640,899.26" "1" "1" "0")
(command "_insert" "blkuc2" "640,898.89" "1" "1" "180")
(command "_insert" "blkuc2" "640,899.63" "1" "1" "0")
(command "_insert" "blkuc2" "640,899.26" "1" "1" "180")
(command "_insert" "blkuc2" "640,900" "1" "1" "0")
(command "_insert" "blkuc2" "640,899.63" "1" "1" "180")
(command "_insert" "blkuc2" "640,900.37" "1" "1" "0")
(command "_insert" "blkuc2" "640,900" "1" "1" "180")
(command "_insert" "blkuc2" "640,900.74" "1" "1" "0")
(command "_insert" "blkuc2" "640,900.37" "1" "1" "180")
(command "_insert" "blkuc2" "640,901.11" "1" "1" "0")
(command "_insert" "blkuc2" "640,900.74" "1" "1" "180")
(command "_insert" "blkuc2" "640,901.48" "1" "1" "0")
(command "_insert" "blkuc2" "640,901.11" "1" "1" "180")
(command "_insert" "blkuc2" "640,901.85" "1" "1" "0")
(command "_insert" "blkuc2" "640,901.48" "1" "1" "180")
(command "_insert" "blkuc2" "640,902.22" "1" "1" "0")
(command "_insert" "blkuc2" "640,901.85" "1" "1" "180")
(command "_insert" "blkuc2" "640,902.59" "1" "1" "0")
(command "_insert" "blkuc2" "640,902.22" "1" "1" "180")
(command "_insert" "blkuc2" "640,902.96" "1" "1" "0")
(command "_insert" "blkuc2" "640,902.59" "1" "1" "180")
(command "_insert" "blkuc2" "640,903.33" "1" "1" "0")
(command "_insert" "blkuc2" "640,902.96" "1" "1" "180")
(command "_insert" "blkuc2" "640,903.7" "1" "1" "0")
(command "_insert" "blkuc2" "640,903.33" "1" "1" "180")
(command "_insert" "blkuc2" "640,904.07" "1" "1" "0")
(command "_insert" "blkuc2" "640,903.7" "1" "1" "180")
(command "_insert" "blkuc2" "640,904.44" "1" "1" "0")
(command "_insert" "blkuc2" "640,904.07" "1" "1" "180")
(command "_insert" "blkuc2" "640,904.81" "1" "1" "0")
(command "_insert" "blkuc2" "640,904.44" "1" "1" "180")
(command "_insert" "blkuc2" "640,905.18" "1" "1" "0")
(command "_insert" "blkuc2" "640,904.81" "1" "1" "180")
(command "_insert" "blkuc2" "640,905.55" "1" "1" "0")
(command "_insert" "blkuc2" "640,905.18" "1" "1" "180")
(command "_insert" "blkuc2" "640,905.92" "1" "1" "0")
(command "_insert" "blkuc2" "640,905.55" "1" "1" "180")
(command "_insert" "blkuc2" "640,906.29" "1" "1" "0")
(command "_insert" "blkuc2" "640,905.92" "1" "1" "180")
(command "_insert" "blkuc2" "640,906.66" "1" "1" "0")
(command "_insert" "blkuc2" "640,906.29" "1" "1" "180")
(command "_insert" "blkuc2" "640,907.03" "1" "1" "0")
(command "_insert" "blkuc2" "640,906.66" "1" "1" "180")
(command "_insert" "blkuc2" "640,907.4" "1" "1" "0")
(command "_insert" "blkuc2" "640,907.03" "1" "1" "180")
(command "_insert" "blkuc2" "640,907.77" "1" "1" "0")
(command "_insert" "blkuc2" "640,907.4" "1" "1" "180")
(command "_insert" "blkuc2" "640,908.14" "1" "1" "0")
(command "_insert" "blkuc2" "640,907.77" "1" "1" "180")
(command "_insert" "blkuc2" "640,908.51" "1" "1" "0")
(command "_insert" "blkuc2" "640,908.14" "1" "1" "180")
(command "_insert" "blkuc2" "640,908.88" "1" "1" "0")
(command "_insert" "blkuc2" "640,908.51" "1" "1" "180")
(command "_insert" "blkuc2" "640,909.25" "1" "1" "0")
(command "_insert" "blkuc2" "640,908.88" "1" "1" "180")
(command "_insert" "blkuc2" "640,909.62" "1" "1" "0")
(command "_insert" "blkuc2" "640,909.25" "1" "1" "180")
(command "_insert" "blkuc2" "640,909.99" "1" "1" "0")
(command "_insert" "blkuc2" "640,909.62" "1" "1" "180")
(command "_insert" "blkuc2" "640,910.36" "1" "1" "0")
(command "_insert" "blkuc2" "640,909.99" "1" "1" "180")
(command "_insert" "blkuc2" "640,910.73" "1" "1" "0")
(command "_insert" "blkuc2" "640,910.36" "1" "1" "180")
(command "_insert" "blkuc2" "640,911.1" "1" "1" "0")
(command "_insert" "blkuc2" "640,910.73" "1" "1" "180")
(command "_insert" "blkuc2" "640,911.47" "1" "1" "0")
(command "_insert" "blkuc2" "640,911.1" "1" "1" "180")
(command "_insert" "blkuc2" "640,911.84" "1" "1" "0")
(command "_insert" "blkuc2" "640,911.47" "1" "1" "180")
(command "_insert" "blkuc2" "640,912.21" "1" "1" "0")
(command "_insert" "blkuc2" "640,911.84" "1" "1" "180")
(command "_insert" "blkuc2" "640,912.58" "1" "1" "0")
(command "_insert" "blkuc2" "640,912.21" "1" "1" "180")
(command "_insert" "blkuc2" "640,912.95" "1" "1" "0")
(command "_insert" "blkuc2" "640,912.58" "1" "1" "180")
(command "_insert" "blkuc2" "640,913.32" "1" "1" "0")
(command "_insert" "blkuc2" "640,912.95" "1" "1" "180")
(command "_insert" "blkuc2" "640,913.69" "1" "1" "0")
(command "_insert" "blkuc2" "640,913.32" "1" "1" "180")
(command "_insert" "blkuc2" "640,914.06" "1" "1" "0")
(command "_insert" "blkuc2" "640,913.69" "1" "1" "180")
(command "_insert" "blkuc2" "640,914.43" "1" "1" "0")
(command "_insert" "blkuc2" "640,914.06" "1" "1" "180")
(command "_insert" "blkuc2" "640,914.8" "1" "1" "0")
(command "_insert" "blkuc2" "640,914.43" "1" "1" "180")
(command "_insert" "blkuc2" "640,915.17" "1" "1" "0")
(command "_insert" "blkuc2" "640,914.8" "1" "1" "180")
(command "_insert" "blkuc2" "640,915.54" "1" "1" "0")
(command "_insert" "blkuc2" "640,915.17" "1" "1" "180")
(command "_insert" "blkuc2" "640,915.91" "1" "1" "0")
(command "_insert" "blkuc2" "640,915.54" "1" "1" "180")
(command "_insert" "blkuc2" "640,916.28" "1" "1" "0")
(command "_insert" "blkuc2" "640,915.91" "1" "1" "180")
(command "_insert" "blkuc2" "640,916.65" "1" "1" "0")
(command "_insert" "blkuc2" "640,916.28" "1" "1" "180")
(command "_insert" "blkuc2" "640,917.02" "1" "1" "0")
(command "_insert" "blkuc2" "640,916.65" "1" "1" "180")
(command "_insert" "blkuc2" "640,917.39" "1" "1" "0")
(command "_insert" "blkuc2" "640,917.02" "1" "1" "180")
(command "_insert" "blkuc2" "640,917.76" "1" "1" "0")
(command "_insert" "blkuc2" "640,917.39" "1" "1" "180")
(command "_insert" "blkuc2" "640,918.13" "1" "1" "0")
(command "_insert" "blkuc2" "640,917.76" "1" "1" "180")
(command "_insert" "blkuc2" "640,918.5" "1" "1" "0")
(command "_insert" "blkuc2" "640,918.13" "1" "1" "180")
(command "_insert" "blkuc2" "640,918.87" "1" "1" "0")
(command "_insert" "blkuc2" "640,918.5" "1" "1" "180")
(command "_insert" "blkuc2" "640,919.24" "1" "1" "0")
(command "_insert" "blkuc2" "640,918.87" "1" "1" "180")
(command "_insert" "blkuc2" "640,919.61" "1" "1" "0")
(command "_insert" "blkuc2" "640,919.24" "1" "1" "180")
(command "_insert" "blkuc2" "640,919.98" "1" "1" "0")
(command "_insert" "blkuc2" "640,919.61" "1" "1" "180")
(command "_insert" "blkuc2" "640,920.35" "1" "1" "0")
(command "_insert" "blkuc2" "640,919.98" "1" "1" "180")
(command "_insert" "blkuc2" "640,920.72" "1" "1" "0")
(command "_insert" "blkuc2" "640,920.35" "1" "1" "180")
(command "_insert" "blkuc2" "640,921.09" "1" "1" "0")
(command "_insert" "blkuc2" "640,920.72" "1" "1" "180")
(command "_insert" "blkuc2" "640,921.46" "1" "1" "0")
(command "_insert" "blkuc2" "640,921.09" "1" "1" "180")
(command "_insert" "blkuc2" "640,921.83" "1" "1" "0")
(command "_insert" "blkuc2" "640,921.46" "1" "1" "180")
(command "_insert" "blkuc2" "640,922.2" "1" "1" "0")
(command "_insert" "blkuc2" "640,921.83" "1" "1" "180")
(command "_insert" "blkuc2" "640,922.57" "1" "1" "0")
(command "_insert" "blkuc2" "640,922.2" "1" "1" "180")
(command "_insert" "blkuc2" "640,922.94" "1" "1" "0")
(command "_insert" "blkuc2" "640,922.57" "1" "1" "180")
(command "_insert" "blkuc2" "640,923.31" "1" "1" "0")
(command "_insert" "blkuc2" "640,922.94" "1" "1" "180")
(command "_insert" "blkuc2" "640,923.68" "1" "1" "0")
(command "_insert" "blkuc2" "640,923.31" "1" "1" "180")
(command "_insert" "blkuc2" "640,924.05" "1" "1" "0")
(command "_insert" "blkuc2" "640,923.68" "1" "1" "180")
(command "_insert" "blkuc2" "640,924.42" "1" "1" "0")
(command "_insert" "blkuc2" "640,924.05" "1" "1" "180")
(command "_insert" "blkuc2" "640,924.79" "1" "1" "0")
(command "_insert" "blkuc2" "640,924.42" "1" "1" "180")
(command "_insert" "blkuc2" "640,925.16" "1" "1" "0")
(command "_insert" "blkuc2" "640,924.79" "1" "1" "180")
(command "_insert" "blkuc2" "640,925.53" "1" "1" "0")
(command "_insert" "blkuc2" "640,925.16" "1" "1" "180")
(command "_insert" "blkuc2" "640,925.9" "1" "1" "0")
(command "_insert" "blkuc2" "640,925.53" "1" "1" "180")
(command "_insert" "blkuc2" "640,926.27" "1" "1" "0")
(command "_insert" "blkuc2" "640,925.9" "1" "1" "180")
(command "_insert" "blkuc2" "640,926.64" "1" "1" "0")
(command "_insert" "blkuc2" "640,926.27" "1" "1" "180")
(command "_insert" "blkuc2" "640,927.01" "1" "1" "0")
(command "_insert" "blkuc2" "640,926.64" "1" "1" "180")
(command "_insert" "blkuc2" "640,927.38" "1" "1" "0")
(command "_insert" "blkuc2" "640,927.01" "1" "1" "180")
(command "_insert" "blkuc2" "640,927.75" "1" "1" "0")
(command "_insert" "blkuc2" "640,927.38" "1" "1" "180")
(command "_layer" "set" "phccover" "")
(command "_rectangle" "638.924,933.3" "641.076,866.7")
(command "_layer" "set" "nitride" "")
(setq phc2 currobj)
(command "_layer" "set" "cover" "")
(command "_rectangle" "638.924,836.7" "641.076,963.3")
(command "_layer" "set" "nitride" "")
(command "_layer" "set" "text" "")
(command "_circle" "637.974,846.7" "0.075")
(command "_circle" "637.599,846.7" "0.15")
(command "_circle" "637.224,846.7" "0.075")
(command "_circle" "636.849,846.7" "0.15")
(command "_circle" "637.974,848.7" "0.075")
(command "_circle" "637.599,848.7" "0.075")
(command "_circle" "637.224,848.7" "0.15")
(command "_circle" "636.849,848.7" "0.15")
(command "_circle" "637.974,850.7" "0.075")
(command "_circle" "637.599,850.7" "0.15")
(command "_circle" "637.224,850.7" "0.15")
(command "_circle" "636.849,850.7" "0.15")
(command "_circle" "637.974,852.7" "0.075")
(command "_circle" "637.599,852.7" "0.075")
(command "_circle" "637.224,852.7" "0.075")
(command "_circle" "636.849,852.7" "0.075")
(command "_circle" "636.474,852.7" "0.15")
(command "_circle" "637.974,854.7" "0.075")
(command "_circle" "637.599,854.7" "0.15")
(command "_circle" "637.224,854.7" "0.075")
(command "_circle" "636.849,854.7" "0.075")
(command "_circle" "636.474,854.7" "0.15")
(command "_circle" "637.974,856.7" "0.075")
(command "_circle" "637.599,856.7" "0.075")
(command "_circle" "637.224,856.7" "0.15")
(command "_circle" "636.849,856.7" "0.075")
(command "_circle" "636.474,856.7" "0.15")
(command "_circle" "637.974,858.7" "0.075")
(command "_circle" "637.599,858.7" "0.15")
(command "_circle" "637.224,858.7" "0.15")
(command "_circle" "636.849,858.7" "0.075")
(command "_circle" "636.474,858.7" "0.15")
(command "_circle" "637.974,860.7" "0.075")
(command "_circle" "637.599,860.7" "0.075")
(command "_circle" "637.224,860.7" "0.075")
(command "_circle" "636.849,860.7" "0.15")
(command "_circle" "636.474,860.7" "0.15")
(command "_circle" "637.974,862.7" "0.075")
(command "_circle" "637.599,862.7" "0.15")
(command "_circle" "637.224,862.7" "0.075")
(command "_circle" "636.849,862.7" "0.15")
(command "_circle" "636.474,862.7" "0.15")
(command "_circle" "637.974,864.7" "0.075")
(command "_circle" "637.599,864.7" "0.075")
(command "_circle" "637.224,864.7" "0.15")
(command "_circle" "636.849,864.7" "0.15")
(command "_circle" "636.474,864.7" "0.15")
(command "_circle" "637.974,866.7" "0.075")
(command "_circle" "637.599,866.7" "0.15")
(command "_circle" "637.224,866.7" "0.15")
(command "_circle" "636.849,866.7" "0.15")
(command "_circle" "636.474,866.7" "0.15")
(command "_circle" "637.974,868.7" "0.075")
(command "_circle" "637.599,868.7" "0.075")
(command "_circle" "637.224,868.7" "0.075")
(command "_circle" "636.849,868.7" "0.075")
(command "_circle" "636.474,868.7" "0.075")
(command "_circle" "636.099,868.7" "0.15")
(command "_circle" "637.974,870.7" "0.075")
(command "_circle" "637.599,870.7" "0.15")
(command "_circle" "637.224,870.7" "0.075")
(command "_circle" "636.849,870.7" "0.075")
(command "_circle" "636.474,870.7" "0.075")
(command "_circle" "636.099,870.7" "0.15")
(command "_circle" "637.974,872.7" "0.075")
(command "_circle" "637.599,872.7" "0.075")
(command "_circle" "637.224,872.7" "0.15")
(command "_circle" "636.849,872.7" "0.075")
(command "_circle" "636.474,872.7" "0.075")
(command "_circle" "636.099,872.7" "0.15")
(command "_circle" "637.974,874.7" "0.075")
(command "_circle" "637.599,874.7" "0.15")
(command "_circle" "637.224,874.7" "0.15")
(command "_circle" "636.849,874.7" "0.075")
(command "_circle" "636.474,874.7" "0.075")
(command "_circle" "636.099,874.7" "0.15")
(command "_circle" "637.974,876.7" "0.075")
(command "_circle" "637.599,876.7" "0.075")
(command "_circle" "637.224,876.7" "0.075")
(command "_circle" "636.849,876.7" "0.15")
(command "_circle" "636.474,876.7" "0.075")
(command "_circle" "636.099,876.7" "0.15")
(command "_circle" "637.974,878.7" "0.075")
(command "_circle" "637.599,878.7" "0.15")
(command "_circle" "637.224,878.7" "0.075")
(command "_circle" "636.849,878.7" "0.15")
(command "_circle" "636.474,878.7" "0.075")
(command "_circle" "636.099,878.7" "0.15")
(command "_circle" "637.974,880.7" "0.075")
(command "_circle" "637.599,880.7" "0.075")
(command "_circle" "637.224,880.7" "0.15")
(command "_circle" "636.849,880.7" "0.15")
(command "_circle" "636.474,880.7" "0.075")
(command "_circle" "636.099,880.7" "0.15")
(command "_circle" "637.974,882.7" "0.075")
(command "_circle" "637.599,882.7" "0.15")
(command "_circle" "637.224,882.7" "0.15")
(command "_circle" "636.849,882.7" "0.15")
(command "_circle" "636.474,882.7" "0.075")
(command "_circle" "636.099,882.7" "0.15")
(command "_circle" "637.974,884.7" "0.075")
(command "_circle" "637.599,884.7" "0.075")
(command "_circle" "637.224,884.7" "0.075")
(command "_circle" "636.849,884.7" "0.075")
(command "_circle" "636.474,884.7" "0.15")
(command "_circle" "636.099,884.7" "0.15")
(command "_circle" "637.974,886.7" "0.075")
(command "_circle" "637.599,886.7" "0.15")
(command "_circle" "637.224,886.7" "0.075")
(command "_circle" "636.849,886.7" "0.075")
(command "_circle" "636.474,886.7" "0.15")
(command "_circle" "636.099,886.7" "0.15")
(command "_circle" "637.974,888.7" "0.075")
(command "_circle" "637.599,888.7" "0.075")
(command "_circle" "637.224,888.7" "0.15")
(command "_circle" "636.849,888.7" "0.075")
(command "_circle" "636.474,888.7" "0.15")
(command "_circle" "636.099,888.7" "0.15")
(command "_circle" "637.974,890.7" "0.075")
(command "_circle" "637.599,890.7" "0.15")
(command "_circle" "637.224,890.7" "0.15")
(command "_circle" "636.849,890.7" "0.075")
(command "_circle" "636.474,890.7" "0.15")
(command "_circle" "636.099,890.7" "0.15")
(command "_circle" "637.974,892.7" "0.075")
(command "_circle" "637.599,892.7" "0.075")
(command "_circle" "637.224,892.7" "0.075")
(command "_circle" "636.849,892.7" "0.15")
(command "_circle" "636.474,892.7" "0.15")
(command "_circle" "636.099,892.7" "0.15")
(command "_circle" "637.974,894.7" "0.075")
(command "_circle" "637.599,894.7" "0.15")
(command "_circle" "637.224,894.7" "0.075")
(command "_circle" "636.849,894.7" "0.15")
(command "_circle" "636.474,894.7" "0.15")
(command "_circle" "636.099,894.7" "0.15")
(command "_circle" "637.974,896.7" "0.075")
(command "_circle" "637.599,896.7" "0.075")
(command "_circle" "637.224,896.7" "0.15")
(command "_circle" "636.849,896.7" "0.15")
(command "_circle" "636.474,896.7" "0.15")
(command "_circle" "636.099,896.7" "0.15")
(command "_circle" "637.974,898.7" "0.075")
(command "_circle" "637.599,898.7" "0.15")
(command "_circle" "637.224,898.7" "0.15")
(command "_circle" "636.849,898.7" "0.15")
(command "_circle" "636.474,898.7" "0.15")
(command "_circle" "636.099,898.7" "0.15")
(command "_circle" "637.974,900.7" "0.075")
(command "_circle" "637.599,900.7" "0.075")
(command "_circle" "637.224,900.7" "0.075")
(command "_circle" "636.849,900.7" "0.075")
(command "_circle" "636.474,900.7" "0.075")
(command "_circle" "636.099,900.7" "0.075")
(command "_circle" "635.724,900.7" "0.15")
(command "_circle" "637.974,902.7" "0.075")
(command "_circle" "637.599,902.7" "0.15")
(command "_circle" "637.224,902.7" "0.075")
(command "_circle" "636.849,902.7" "0.075")
(command "_circle" "636.474,902.7" "0.075")
(command "_circle" "636.099,902.7" "0.075")
(command "_circle" "635.724,902.7" "0.15")
(command "_circle" "637.974,904.7" "0.075")
(command "_circle" "637.599,904.7" "0.075")
(command "_circle" "637.224,904.7" "0.15")
(command "_circle" "636.849,904.7" "0.075")
(command "_circle" "636.474,904.7" "0.075")
(command "_circle" "636.099,904.7" "0.075")
(command "_circle" "635.724,904.7" "0.15")
(command "_circle" "637.974,906.7" "0.075")
(command "_circle" "637.599,906.7" "0.15")
(command "_circle" "637.224,906.7" "0.15")
(command "_circle" "636.849,906.7" "0.075")
(command "_circle" "636.474,906.7" "0.075")
(command "_circle" "636.099,906.7" "0.075")
(command "_circle" "635.724,906.7" "0.15")
(command "_circle" "637.974,908.7" "0.075")
(command "_circle" "637.599,908.7" "0.075")
(command "_circle" "637.224,908.7" "0.075")
(command "_circle" "636.849,908.7" "0.15")
(command "_circle" "636.474,908.7" "0.075")
(command "_circle" "636.099,908.7" "0.075")
(command "_circle" "635.724,908.7" "0.15")
(command "_circle" "637.974,910.7" "0.075")
(command "_circle" "637.599,910.7" "0.15")
(command "_circle" "637.224,910.7" "0.075")
(command "_circle" "636.849,910.7" "0.15")
(command "_circle" "636.474,910.7" "0.075")
(command "_circle" "636.099,910.7" "0.075")
(command "_circle" "635.724,910.7" "0.15")
(command "_circle" "637.974,912.7" "0.075")
(command "_circle" "637.599,912.7" "0.075")
(command "_circle" "637.224,912.7" "0.15")
(command "_circle" "636.849,912.7" "0.15")
(command "_circle" "636.474,912.7" "0.075")
(command "_circle" "636.099,912.7" "0.075")
(command "_circle" "635.724,912.7" "0.15")
(command "_circle" "637.974,914.7" "0.075")
(command "_circle" "637.599,914.7" "0.15")
(command "_circle" "637.224,914.7" "0.15")
(command "_circle" "636.849,914.7" "0.15")
(command "_circle" "636.474,914.7" "0.075")
(command "_circle" "636.099,914.7" "0.075")
(command "_circle" "635.724,914.7" "0.15")
(command "_circle" "637.974,916.7" "0.075")
(command "_circle" "637.599,916.7" "0.075")
(command "_circle" "637.224,916.7" "0.075")
(command "_circle" "636.849,916.7" "0.075")
(command "_circle" "636.474,916.7" "0.15")
(command "_circle" "636.099,916.7" "0.075")
(command "_circle" "635.724,916.7" "0.15")
(command "_circle" "637.974,918.7" "0.075")
(command "_circle" "637.599,918.7" "0.15")
(command "_circle" "637.224,918.7" "0.075")
(command "_circle" "636.849,918.7" "0.075")
(command "_circle" "636.474,918.7" "0.15")
(command "_circle" "636.099,918.7" "0.075")
(command "_circle" "635.724,918.7" "0.15")
(command "_circle" "637.974,920.7" "0.075")
(command "_circle" "637.599,920.7" "0.075")
(command "_circle" "637.224,920.7" "0.15")
(command "_circle" "636.849,920.7" "0.075")
(command "_circle" "636.474,920.7" "0.15")
(command "_circle" "636.099,920.7" "0.075")
(command "_circle" "635.724,920.7" "0.15")
(command "_circle" "637.974,922.7" "0.075")
(command "_circle" "637.599,922.7" "0.15")
(command "_circle" "637.224,922.7" "0.15")
(command "_circle" "636.849,922.7" "0.075")
(command "_circle" "636.474,922.7" "0.15")
(command "_circle" "636.099,922.7" "0.075")
(command "_circle" "635.724,922.7" "0.15")
(command "_circle" "637.974,924.7" "0.075")
(command "_circle" "637.599,924.7" "0.075")
(command "_circle" "637.224,924.7" "0.075")
(command "_circle" "636.849,924.7" "0.15")
(command "_circle" "636.474,924.7" "0.15")
(command "_circle" "636.099,924.7" "0.075")
(command "_circle" "635.724,924.7" "0.15")
(command "_circle" "637.974,926.7" "0.075")
(command "_circle" "637.599,926.7" "0.15")
(command "_circle" "637.224,926.7" "0.075")
(command "_circle" "636.849,926.7" "0.15")
(command "_circle" "636.474,926.7" "0.15")
(command "_circle" "636.099,926.7" "0.075")
(command "_circle" "635.724,926.7" "0.15")
(command "_circle" "637.974,928.7" "0.075")
(command "_circle" "637.599,928.7" "0.075")
(command "_circle" "637.224,928.7" "0.15")
(command "_circle" "636.849,928.7" "0.15")
(command "_circle" "636.474,928.7" "0.15")
(command "_circle" "636.099,928.7" "0.075")
(command "_circle" "635.724,928.7" "0.15")
(command "_circle" "637.974,930.7" "0.075")
(command "_circle" "637.599,930.7" "0.15")
(command "_circle" "637.224,930.7" "0.15")
(command "_circle" "636.849,930.7" "0.15")
(command "_circle" "636.474,930.7" "0.15")
(command "_circle" "636.099,930.7" "0.075")
(command "_circle" "635.724,930.7" "0.15")
(command "_circle" "637.974,932.7" "0.075")
(command "_circle" "637.599,932.7" "0.075")
(command "_circle" "637.224,932.7" "0.075")
(command "_circle" "636.849,932.7" "0.075")
(command "_circle" "636.474,932.7" "0.075")
(command "_circle" "636.099,932.7" "0.15")
(command "_circle" "635.724,932.7" "0.15")
(command "_circle" "637.974,934.7" "0.075")
(command "_circle" "637.599,934.7" "0.15")
(command "_circle" "637.224,934.7" "0.075")
(command "_circle" "636.849,934.7" "0.075")
(command "_circle" "636.474,934.7" "0.075")
(command "_circle" "636.099,934.7" "0.15")
(command "_circle" "635.724,934.7" "0.15")
(command "_circle" "637.974,936.7" "0.075")
(command "_circle" "637.599,936.7" "0.075")
(command "_circle" "637.224,936.7" "0.15")
(command "_circle" "636.849,936.7" "0.075")
(command "_circle" "636.474,936.7" "0.075")
(command "_circle" "636.099,936.7" "0.15")
(command "_circle" "635.724,936.7" "0.15")
(command "_circle" "637.974,938.7" "0.075")
(command "_circle" "637.599,938.7" "0.15")
(command "_circle" "637.224,938.7" "0.15")
(command "_circle" "636.849,938.7" "0.075")
(command "_circle" "636.474,938.7" "0.075")
(command "_circle" "636.099,938.7" "0.15")
(command "_circle" "635.724,938.7" "0.15")
(command "_circle" "637.974,940.7" "0.075")
(command "_circle" "637.599,940.7" "0.075")
(command "_circle" "637.224,940.7" "0.075")
(command "_circle" "636.849,940.7" "0.15")
(command "_circle" "636.474,940.7" "0.075")
(command "_circle" "636.099,940.7" "0.15")
(command "_circle" "635.724,940.7" "0.15")
(command "_circle" "637.974,942.7" "0.075")
(command "_circle" "637.599,942.7" "0.15")
(command "_circle" "637.224,942.7" "0.075")
(command "_circle" "636.849,942.7" "0.15")
(command "_circle" "636.474,942.7" "0.075")
(command "_circle" "636.099,942.7" "0.15")
(command "_circle" "635.724,942.7" "0.15")
(command "_circle" "637.974,944.7" "0.075")
(command "_circle" "637.599,944.7" "0.075")
(command "_circle" "637.224,944.7" "0.15")
(command "_circle" "636.849,944.7" "0.15")
(command "_circle" "636.474,944.7" "0.075")
(command "_circle" "636.099,944.7" "0.15")
(command "_circle" "635.724,944.7" "0.15")
(command "_circle" "637.974,946.7" "0.075")
(command "_circle" "637.599,946.7" "0.15")
(command "_circle" "637.224,946.7" "0.15")
(command "_circle" "636.849,946.7" "0.15")
(command "_circle" "636.474,946.7" "0.075")
(command "_circle" "636.099,946.7" "0.15")
(command "_circle" "635.724,946.7" "0.15")
(command "_circle" "637.974,948.7" "0.075")
(command "_circle" "637.599,948.7" "0.075")
(command "_circle" "637.224,948.7" "0.075")
(command "_circle" "636.849,948.7" "0.075")
(command "_circle" "636.474,948.7" "0.15")
(command "_circle" "636.099,948.7" "0.15")
(command "_circle" "635.724,948.7" "0.15")
(command "_circle" "637.974,950.7" "0.075")
(command "_circle" "637.599,950.7" "0.15")
(command "_circle" "637.224,950.7" "0.075")
(command "_circle" "636.849,950.7" "0.075")
(command "_circle" "636.474,950.7" "0.15")
(command "_circle" "636.099,950.7" "0.15")
(command "_circle" "635.724,950.7" "0.15")
(command "_circle" "637.974,952.7" "0.075")
(command "_circle" "637.599,952.7" "0.075")
(command "_circle" "637.224,952.7" "0.15")
(command "_circle" "636.849,952.7" "0.075")
(command "_circle" "636.474,952.7" "0.15")
(command "_circle" "636.099,952.7" "0.15")
(command "_circle" "635.724,952.7" "0.15")
(command "_circle" "637.974,954.7" "0.075")
(command "_circle" "637.599,954.7" "0.15")
(command "_circle" "637.224,954.7" "0.15")
(command "_circle" "636.849,954.7" "0.075")
(command "_circle" "636.474,954.7" "0.15")
(command "_circle" "636.099,954.7" "0.15")
(command "_circle" "635.724,954.7" "0.15")
(command "_circle" "637.974,956.7" "0.075")
(command "_circle" "637.599,956.7" "0.075")
(command "_circle" "637.224,956.7" "0.075")
(command "_circle" "636.849,956.7" "0.15")
(command "_circle" "636.474,956.7" "0.15")
(command "_circle" "636.099,956.7" "0.15")
(command "_circle" "635.724,956.7" "0.15")
(command "_circle" "637.974,958.7" "0.075")
(command "_circle" "637.599,958.7" "0.15")
(command "_circle" "637.224,958.7" "0.075")
(command "_circle" "636.849,958.7" "0.15")
(command "_circle" "636.474,958.7" "0.15")
(command "_circle" "636.099,958.7" "0.15")
(command "_circle" "635.724,958.7" "0.15")
(command "_circle" "637.974,960.7" "0.075")
(command "_circle" "637.599,960.7" "0.075")
(command "_circle" "637.224,960.7" "0.15")
(command "_circle" "636.849,960.7" "0.15")
(command "_circle" "636.474,960.7" "0.15")
(command "_circle" "636.099,960.7" "0.15")
(command "_circle" "635.724,960.7" "0.15")
(command "_circle" "637.974,962.7" "0.075")
(command "_circle" "637.599,962.7" "0.15")
(command "_circle" "637.224,962.7" "0.15")
(command "_circle" "636.849,962.7" "0.15")
(command "_circle" "636.474,962.7" "0.15")
(command "_circle" "636.099,962.7" "0.15")
(command "_circle" "635.724,962.7" "0.15")
(command "_layer" "set" "nitride" "")
(command "_layer" "set" "text" "")
(command-s "_text" "626.924,963.3" "2" "-90" "a = 370 nm" )
(sssetfirst nil (ssget "_L"))
(if (not (numberp (vl-string-search "Mac" (getvar "platform")))) (c:txtexp))
(command "_layer" "set" "nitride" "")
(command "_layer" "set" "text" "")
(command-s "_text" "623.924,963.3" "2" "-90" "gap = 270 nm" )
(sssetfirst nil (ssget "_L"))
(if (not (numberp (vl-string-search "Mac" (getvar "platform")))) (c:txtexp))
(command "_layer" "set" "nitride" "")
(command "_layer" "set" "text" "")
(command-s "_text" "620.924,963.3" "2" "-90" "amplitude = 127 nm" )
(sssetfirst nil (ssget "_L"))
(if (not (numberp (vl-string-search "Mac" (getvar "platform")))) (c:txtexp))
(command "_layer" "set" "nitride" "")
(command "_layer" "set" "text" "")
(command-s "_text" "617.924,963.3" "2" "-90" "start width = 280 nm" )
(sssetfirst nil (ssget "_L"))
(if (not (numberp (vl-string-search "Mac" (getvar "platform")))) (c:txtexp))
(command "_layer" "set" "nitride" "")
(command "_layer" "set" "text" "")
(command-s "_text" "614.924,963.3" "2" "-90" "width = 276 nm" )
(sssetfirst nil (ssget "_L"))
(if (not (numberp (vl-string-search "Mac" (getvar "platform")))) (c:txtexp))
(command "_layer" "set" "nitride" "")
(command "_layer" "set" "text" "")
(command-s "_text" "611.924,963.3" "2" "-90" "taper: 15" )
(sssetfirst nil (ssget "_L"))
(if (not (numberp (vl-string-search "Mac" (getvar "platform")))) (c:txtexp))
(command "_layer" "set" "nitride" "")
(command "_layer" "set" "text" "")
(command-s "_text" "608.924,963.3" "2" "-90" "nominal: 150" )
(sssetfirst nil (ssget "_L"))
(if (not (numberp (vl-string-search "Mac" (getvar "platform")))) (c:txtexp))
(command "_layer" "set" "nitride" "")
(command "_layer" "set" "indicators" "")
(setq coords (list 
(list 560.415 940) 
(list 560.415 920) 
(list 540.415 900) 
(list 560.415 880) 
(list 560.415 860) 
(list 560.415 900) 
(list 560.415 887.0711) 
(list 547.4861 900) 
(list 560.415 912.9289) 
(list 560.415 900)))
(apply 'command (append '("pline") coords '("c")))
(command "._fillet" "radius" "1" "._fillet" "P" (entlast))
(setq coords (list 
(list 719.585 940) 
(list 719.585 920) 
(list 739.585 900) 
(list 719.585 880) 
(list 719.585 860) 
(list 719.585 900) 
(list 719.585 887.0711) 
(list 732.5139 900) 
(list 719.585 912.9289) 
(list 719.585 900)))
(apply 'command (append '("pline") coords '("c")))
(command "._fillet" "radius" "1" "._fillet" "P" (entlast))
(command "_layer" "set" "holes" "")
(command "_circle" "558.0629,914.1124" "0.5")
(command "_circle" "555.7109,911.7603" "0.5")
(command "_circle" "553.3588,909.4083" "0.5")
(command "_circle" "551.0067,907.0562" "0.5")
(command "_circle" "548.6547,904.7041" "0.5")
(command "_circle" "546.3026,902.3521" "0.5")
(command "_circle" "543.9505,900" "0.5")
(command "_circle" "546.3026,897.6479" "0.5")
(command "_circle" "548.6547,895.2959" "0.5")
(command "_circle" "551.0067,892.9438" "0.5")
(command "_circle" "553.3588,890.5917" "0.5")
(command "_circle" "555.7109,888.2397" "0.5")
(command "_circle" "558.0629,885.8876" "0.5")
(command "_circle" "721.9371,914.1124" "0.5")
(command "_circle" "724.2891,911.7603" "0.5")
(command "_circle" "726.6412,909.4083" "0.5")
(command "_circle" "728.9933,907.0562" "0.5")
(command "_circle" "731.3453,904.7041" "0.5")
(command "_circle" "733.6974,902.3521" "0.5")
(command "_circle" "736.0495,900" "0.5")
(command "_circle" "733.6974,897.6479" "0.5")
(command "_circle" "731.3453,895.2959" "0.5")
(command "_circle" "728.9933,892.9438" "0.5")
(command "_circle" "726.6412,890.5917" "0.5")
(command "_circle" "724.2891,888.2397" "0.5")
(command "_circle" "721.9371,885.8876" "0.5")
(command "_layer" "set" "nitride" "")
(command "_block" "blkcoupler2" "640,900" coupler2 "")
(command "_insert" "blkcoupler2" "640,900" "1" "1" "0")
(command "_insert" "blkcoupler2" "640,900" "1" "1" "180")
(command "_block" "blksinglenanobeam2" "640,900" singlenanobeam2 "")
(command "_insert" "blksinglenanobeam2" "640,900" "1" "1" "0")
(command "_insert" "blksinglenanobeam2" "640,900" "1" "1" "180")
(command "_block" "blkanglednodearray2" "640,900" anglednodearray2 "")
(command "_insert" "blkanglednodearray2" "640,900" "1" "1" "0")
(command "_insert" "blkanglednodearray2" "640,900" "1" "1" "180")
(command "_block" "blkcooledsinglenanobeam2" "640,900" cooledsinglenanobeam2 "")
(command "_insert" "blkcooledsinglenanobeam2" "640,900" "1" "1" "0")
(command "_insert" "blkcooledsinglenanobeam2" "640,900" "1" "1" "180")
(command "_block" "blkyjunction2" "640,900" yjunction2 "")
(command "_insert" "blkyjunction2" "640,900" "1" "1" "0")
(command "_insert" "blkyjunction2" "640,900" "1" "1" "180")
; DRAWING BULGING VEE GROOVE
(command "_layer" "set" "vgroove" "")
(setq coords (list 
(list 565.415 -605) 
(list 565.415 0) 
(list 565.415 0) 
(list 565.415 1800) 
(list 565.415 1800) 
(list 565.415 2405) 
(list 714.585 2405) 
(list 714.585 1800) 
(list 714.585 1800) 
(list 714.585 0) 
(list 714.585 0) 
(list 714.585 -605)))
(apply 'command (append '("pline") coords '("c")))
(command "._fillet" "radius" "0" "._fillet" "P" (entlast))
(command "_layer" "set" "window" "")
(command "_rectangle" "565.415,-1935" "714.585,-600")
(command "_rectangle" "565.415,2400" "714.585,5300")
(command "_layer" "set" "grid" "")
(command "_rectangle" "566.415,-1934" "589.9433,-1909.2133")
(command "_array" "last" "" "R" "75" "3" "25.7867" "24.5283")
(command "_rectangle" "641,-1934" "664.5283,-1909.2133")
(command "_array" "last" "" "R" "75" "3" "25.7867" "24.5283")
(command "_rectangle" "566.415,1" "589.9433,25.7")
(command "_array" "last" "" "R" "70" "3" "25.7" "24.5283")
(command "_rectangle" "641,1" "664.5283,25.7")
(command "_array" "last" "" "R" "70" "3" "25.7" "24.5283")
(command "_rectangle" "566.415,1801" "589.9433,1825.9185")
(command "_array" "last" "" "R" "135" "3" "25.9185" "24.5283")
(command "_rectangle" "641,1801" "664.5283,1825.9185")
(command "_array" "last" "" "R" "135" "3" "25.9185" "24.5283")
(command "_layer" "set" "vgrooveFDA" "")
(command "_rectangle" "714.585,-2233" "565.415,-1933")
(command "_layer" "set" "nitride" "")
(command "_layer" "set" "holes" "")
(command "_circle" "717.085,331.5" "0.5")
(command "_array" "last" "" "R" "379" "1" "3" "2.5")
(command "_circle" "562.915,331.5" "0.5")
(command "_array" "last" "" "R" "379" "1" "3" "-2.5")
(command "_layer" "set" "nitride" "")
(command "_layer" "set" "window" "")
(command "_layer" "set" "window" "")
(command "_rectangle" "719.585,0" "880.415,1800")
(command "._fillet" "radius" "20" "._fillet" "P" (entlast))
(command "_layer" "set" "grid" "")
(command "_rectangle" "720.585,1" "742.4179,25.7")
(command "_array" "last" "" "R" "70" "7" "25.7" "22.8329")
(command "_layer" "set" "nitride" "")
; DRAWING REGION LAYER
(command "_layer" "set" "regionLayer2" "")
(command "_rectangle" "560,-460" "720,2260")
(command "_layer" "set" "nitride" "")
(setq coupler2 nil)
(setq singlenanobeam2 nil)
(setq anglednodearray2 nil)
(setq cooledsinglenanobeam2 nil)
(setq yjunction2 nil)
; DEVICE #3
(command "_layer" "set" "window" "")
(command "_circle" "872.915,-415" "5")
(command "_circle" "872.915,-402.5" "5")
(command "_circle" "872.915,-390" "5")
(command "_layer" "set" "nitride" "")
(setq currobj nil)
(setq currobj (ssadd))
; DRAWING COUPLER
(setq coords (list 
(list 960.0615 -415) 
(list 960.0615 -413) 
(list 1033.585 -413) 
(list 1033.585 -413) 
(list 1033.9677 -413.0761) 
(list 1034.2921 -413.2929) 
(list 1034.5089 -413.6173) 
(list 1034.585 -414) 
(list 1034.585 -411.8) 
(list 1034.585 -411.8) 
(list 1034.5089 -412.1827) 
(list 1034.2921 -412.5071) 
(list 1033.9677 -412.7239) 
(list 1033.585 -412.8) 
(list 960.0615 -412.8) 
(list 960.0615 -410.8) 
(list 959.9385 -410.8) 
(list 959.9385 -412.8) 
(list 886.415 -412.8) 
(list 886.0323 -412.7239) 
(list 885.7079 -412.5071) 
(list 885.4911 -412.1827) 
(list 885.415 -411.8) 
(list 885.415 -411.8) 
(list 885.415 -414) 
(list 885.4911 -413.6173) 
(list 885.7079 -413.2929) 
(list 886.0323 -413.0761) 
(list 886.415 -413) 
(list 886.415 -413) 
(list 959.9385 -413) 
(list 959.9385 -415)))
(apply 'command (append '("pline") coords '("c")))
(setq currobj (ssadd (entlast) currobj))
(command "._fillet" "radius" "0.3" "._fillet" "P" (entlast))
(command "_layer" "set" "holes" "")
(command "_circle" "960,-412.9" "0.113")
(setq currobj (ssadd (entlast) currobj))
(command "_layer" "set" "nitride" "")
(command "_layer" "set" "text" "")
(command "_circle" "959.2,-415" "0.075")
(command "_circle" "959.2,-414.7" "0.075")
(command "_circle" "959.2,-414.4" "0.075")
(command "_circle" "958.9,-415" "0.075")
(command "_circle" "958.9,-414.7" "0.075")
(command "_circle" "958.9,-414.4" "0.075")
(command "_circle" "958.6,-415" "0.075")
(command "_circle" "958.6,-414.7" "0.075")
(command "_circle" "958.6,-414.4" "0.075")
(command "_layer" "set" "nitride" "")
(command "_layer" "set" "prebias" "")
(command "_rectangle" "885.415,-414" "1034.585,-411.8")
(setq currobj (ssadd (entlast) currobj))
(command "_rectangle" "959.9385,-415" "960.0615,-410.8")
(setq currobj (ssadd (entlast) currobj))
(command "_layer" "set" "nitride" "")
(setq coupler3 currobj)
(setq currobj nil)
(setq currobj (ssadd))
; DRAWING SINGLE NANOBEAM
(setq coords (list 
(list 960.0615 -410.8) 
(list 960.0615 -409.1417) 
(list 960.0615 -407.4833) 
(list 960.0615 -405.825) 
(list 960.0615 -404.1667) 
(list 960.0615 -402.5083) 
(list 960.0615 -400.85) 
(list 960.0615 -399.1917) 
(list 960.0615 -397.5333) 
(list 960.0616 -395.875) 
(list 960.0616 -394.2167) 
(list 960.0616 -392.5583) 
(list 960.0616 -390.9) 
(list 960.0617 -389.2417) 
(list 960.0617 -387.5833) 
(list 960.0617 -385.925) 
(list 960.0618 -384.2667) 
(list 960.0619 -382.6083) 
(list 960.0619 -380.95) 
(list 960.062 -379.2917) 
(list 960.0621 -377.6333) 
(list 960.0622 -375.975) 
(list 960.0623 -374.3167) 
(list 960.0624 -372.6583) 
(list 960.0625 -371) 
(list 960.0626 -369.3417) 
(list 960.0628 -367.6833) 
(list 960.0629 -366.025) 
(list 960.0631 -364.3667) 
(list 960.0632 -362.7083) 
(list 960.0634 -361.05) 
(list 960.0636 -359.3917) 
(list 960.0638 -357.7333) 
(list 960.0641 -356.075) 
(list 960.0643 -354.4167) 
(list 960.0646 -352.7583) 
(list 960.0648 -351.1) 
(list 960.0651 -349.4417) 
(list 960.0654 -347.7833) 
(list 960.0657 -346.125) 
(list 960.0661 -344.4667) 
(list 960.0664 -342.8083) 
(list 960.0668 -341.15) 
(list 960.0672 -339.4917) 
(list 960.0676 -337.8333) 
(list 960.068 -336.175) 
(list 960.0685 -334.5167) 
(list 960.0689 -332.8583) 
(list 960.0694 -331.2) 
(list 960.0699 -329.5417) 
(list 960.0704 -327.8833) 
(list 960.071 -326.225) 
(list 960.0715 -324.5667) 
(list 960.0721 -322.9083) 
(list 960.0728 -321.25) 
(list 960.0734 -319.5917) 
(list 960.0741 -317.9333) 
(list 960.0747 -316.275) 
(list 960.0754 -314.6167) 
(list 960.0762 -312.9583) 
(list 960.0769 -311.3) 
(list 960.0777 -309.6417) 
(list 960.0785 -307.9833) 
(list 960.0794 -306.325) 
(list 960.0802 -304.6667) 
(list 960.0811 -303.0083) 
(list 960.082 -301.35) 
(list 960.083 -299.6917) 
(list 960.084 -298.0333) 
(list 960.085 -296.375) 
(list 960.086 -294.7167) 
(list 960.0871 -293.0583) 
(list 960.0882 -291.4) 
(list 960.0893 -289.7417) 
(list 960.0905 -288.0833) 
(list 960.0917 -286.425) 
(list 960.0929 -284.7667) 
(list 960.0941 -283.1083) 
(list 960.0954 -281.45) 
(list 960.0967 -279.7917) 
(list 960.0981 -278.1333) 
(list 960.0995 -276.475) 
(list 960.1009 -274.8167) 
(list 960.1024 -273.1583) 
(list 960.1039 -271.5) 
(list 960.1054 -269.8417) 
(list 960.107 -268.1833) 
(list 960.1086 -266.525) 
(list 960.1102 -264.8667) 
(list 960.1119 -263.2083) 
(list 960.1136 -261.55) 
(list 960.1154 -259.8917) 
(list 960.1172 -258.2333) 
(list 960.119 -256.575) 
(list 960.1209 -254.9167) 
(list 960.1228 -253.2583) 
(list 960.1247 -251.6) 
(list 960.1267 -249.9417) 
(list 960.1288 -248.2833) 
(list 960.1308 -246.625) 
(list 960.133 -244.9667) 
(list 960.1351 -243.3083) 
(list 960.1373 -241.65) 
(list 960.1396 -239.9917) 
(list 960.1419 -238.3333) 
(list 960.1442 -236.675) 
(list 960.1466 -235.0167) 
(list 960.1491 -233.3583) 
(list 960.1515 -231.7) 
(list 960.1541 -230.0417) 
(list 960.1566 -228.3833) 
(list 960.1592 -226.725) 
(list 960.1619 -225.0667) 
(list 960.1646 -223.4083) 
(list 960.1674 -221.75) 
(list 960.1702 -220.0917) 
(list 960.1731 -218.4333) 
(list 960.176 -216.775) 
(list 960.1789 -215.1167) 
(list 960.1819 -213.4583) 
(list 960.185 -211.8) 
(list 959.815 -211.8) 
(list 959.8181 -213.4583) 
(list 959.8211 -215.1167) 
(list 959.824 -216.775) 
(list 959.8269 -218.4333) 
(list 959.8298 -220.0917) 
(list 959.8326 -221.75) 
(list 959.8354 -223.4083) 
(list 959.8381 -225.0667) 
(list 959.8408 -226.725) 
(list 959.8434 -228.3833) 
(list 959.8459 -230.0417) 
(list 959.8485 -231.7) 
(list 959.8509 -233.3583) 
(list 959.8534 -235.0167) 
(list 959.8558 -236.675) 
(list 959.8581 -238.3333) 
(list 959.8604 -239.9917) 
(list 959.8627 -241.65) 
(list 959.8649 -243.3083) 
(list 959.867 -244.9667) 
(list 959.8692 -246.625) 
(list 959.8712 -248.2833) 
(list 959.8733 -249.9417) 
(list 959.8753 -251.6) 
(list 959.8772 -253.2583) 
(list 959.8791 -254.9167) 
(list 959.881 -256.575) 
(list 959.8828 -258.2333) 
(list 959.8846 -259.8917) 
(list 959.8864 -261.55) 
(list 959.8881 -263.2083) 
(list 959.8898 -264.8667) 
(list 959.8914 -266.525) 
(list 959.893 -268.1833) 
(list 959.8946 -269.8417) 
(list 959.8961 -271.5) 
(list 959.8976 -273.1583) 
(list 959.8991 -274.8167) 
(list 959.9005 -276.475) 
(list 959.9019 -278.1333) 
(list 959.9033 -279.7917) 
(list 959.9046 -281.45) 
(list 959.9059 -283.1083) 
(list 959.9071 -284.7667) 
(list 959.9083 -286.425) 
(list 959.9095 -288.0833) 
(list 959.9107 -289.7417) 
(list 959.9118 -291.4) 
(list 959.9129 -293.0583) 
(list 959.914 -294.7167) 
(list 959.915 -296.375) 
(list 959.916 -298.0333) 
(list 959.917 -299.6917) 
(list 959.918 -301.35) 
(list 959.9189 -303.0083) 
(list 959.9198 -304.6667) 
(list 959.9206 -306.325) 
(list 959.9215 -307.9833) 
(list 959.9223 -309.6417) 
(list 959.9231 -311.3) 
(list 959.9238 -312.9583) 
(list 959.9246 -314.6167) 
(list 959.9253 -316.275) 
(list 959.9259 -317.9333) 
(list 959.9266 -319.5917) 
(list 959.9272 -321.25) 
(list 959.9279 -322.9083) 
(list 959.9285 -324.5667) 
(list 959.929 -326.225) 
(list 959.9296 -327.8833) 
(list 959.9301 -329.5417) 
(list 959.9306 -331.2) 
(list 959.9311 -332.8583) 
(list 959.9315 -334.5167) 
(list 959.932 -336.175) 
(list 959.9324 -337.8333) 
(list 959.9328 -339.4917) 
(list 959.9332 -341.15) 
(list 959.9336 -342.8083) 
(list 959.9339 -344.4667) 
(list 959.9343 -346.125) 
(list 959.9346 -347.7833) 
(list 959.9349 -349.4417) 
(list 959.9352 -351.1) 
(list 959.9354 -352.7583) 
(list 959.9357 -354.4167) 
(list 959.9359 -356.075) 
(list 959.9362 -357.7333) 
(list 959.9364 -359.3917) 
(list 959.9366 -361.05) 
(list 959.9368 -362.7083) 
(list 959.9369 -364.3667) 
(list 959.9371 -366.025) 
(list 959.9372 -367.6833) 
(list 959.9374 -369.3417) 
(list 959.9375 -371) 
(list 959.9376 -372.6583) 
(list 959.9377 -374.3167) 
(list 959.9378 -375.975) 
(list 959.9379 -377.6333) 
(list 959.938 -379.2917) 
(list 959.9381 -380.95) 
(list 959.9381 -382.6083) 
(list 959.9382 -384.2667) 
(list 959.9383 -385.925) 
(list 959.9383 -387.5833) 
(list 959.9383 -389.2417) 
(list 959.9384 -390.9) 
(list 959.9384 -392.5583) 
(list 959.9384 -394.2167) 
(list 959.9384 -395.875) 
(list 959.9385 -397.5333) 
(list 959.9385 -399.1917) 
(list 959.9385 -400.85) 
(list 959.9385 -402.5083) 
(list 959.9385 -404.1667) 
(list 959.9385 -405.825) 
(list 959.9385 -407.4833) 
(list 959.9385 -409.1417) 
(list 959.9385 -410.8)))
(apply 'command (append '("pline") coords '("c")))
(setq currobj (ssadd (entlast) currobj))
(command "_layer" "set" "prebias" "")
(command "_rectangle" "959.815,-410.8" "960.185,-211.8")
(setq currobj (ssadd (entlast) currobj))
(command "_layer" "set" "nitride" "")
(setq singlenanobeam3 currobj)
(setq currobj nil)
(setq currobj (ssadd))
; DRAWING NODE ARRAY
(setq coords (list 
(list 960.185 -211.8) 
(list 960.5625 -201.8) 
(list 960.5625 -201.8) 
(list 960.5625 -200.8) 
(list 1034.585 -212.6864) 
(list 1034.585 -207.7434) 
(list 960.5625 -197.357) 
(list 960.5625 -196.357) 
(list 960.5625 -196.357) 
(list 960.2625 -186.357) 
(list 959.7375 -186.357) 
(list 959.4375 -196.357) 
(list 959.4375 -196.357) 
(list 959.4375 -197.357) 
(list 885.415 -207.7434) 
(list 885.415 -212.6864) 
(list 959.4375 -200.8) 
(list 959.4375 -201.8) 
(list 959.4375 -201.8) 
(list 959.815 -211.8)))
(apply 'command (append '("pline") coords '("c")))
(setq currobj (ssadd (entlast) currobj))
(command "_layer" "set" "prebias" "")
(setq coords (list 
(list 959.4375 -212.6864) 
(list 959.4375 -200.8) 
(list 885.415 -212.6864) 
(list 885.415 -207.7434) 
(list 959.4375 -197.357) 
(list 959.4375 -186.357) 
(list 960.5625 -186.357) 
(list 960.5625 -197.357) 
(list 1034.585 -207.7434) 
(list 1034.585 -212.6864) 
(list 960.5625 -200.8) 
(list 960.5625 -212.6864)))
(apply 'command (append '("pline") coords '("c")))
(setq currobj (ssadd (entlast) currobj))
(command "_layer" "set" "nitride" "")
(command "_layer" "set" "fda1" "")
(setq coords (list 
(list 960.5625 -200.657) 
(list 1034.585 -212.5434) 
(list 1034.585 -212.3664) 
(list 960.5625 -200.58)))
(apply 'command (append '("pline") coords '("c")))
(setq currobj (ssadd (entlast) currobj))
(setq coords (list 
(list 960.5625 -200.437) 
(list 1034.585 -212.2234) 
(list 1034.585 -212.0464) 
(list 960.5625 -200.36)))
(apply 'command (append '("pline") coords '("c")))
(setq currobj (ssadd (entlast) currobj))
(setq coords (list 
(list 960.5625 -200.217) 
(list 1034.585 -211.9034) 
(list 1034.585 -211.7264) 
(list 960.5625 -200.14)))
(apply 'command (append '("pline") coords '("c")))
(setq currobj (ssadd (entlast) currobj))
(setq coords (list 
(list 960.5625 -199.997) 
(list 1034.585 -211.5834) 
(list 1034.585 -211.4064) 
(list 960.5625 -199.92)))
(apply 'command (append '("pline") coords '("c")))
(setq currobj (ssadd (entlast) currobj))
(setq coords (list 
(list 960.5625 -199.777) 
(list 1034.585 -211.2634) 
(list 1034.585 -211.0864) 
(list 960.5625 -199.7)))
(apply 'command (append '("pline") coords '("c")))
(setq currobj (ssadd (entlast) currobj))
(setq coords (list 
(list 960.5625 -199.557) 
(list 1034.585 -210.9434) 
(list 1034.585 -210.7664) 
(list 960.5625 -199.48)))
(apply 'command (append '("pline") coords '("c")))
(setq currobj (ssadd (entlast) currobj))
(setq coords (list 
(list 960.5625 -199.337) 
(list 1034.585 -210.6234) 
(list 1034.585 -210.4464) 
(list 960.5625 -199.26)))
(apply 'command (append '("pline") coords '("c")))
(setq currobj (ssadd (entlast) currobj))
(setq coords (list 
(list 960.5625 -199.117) 
(list 1034.585 -210.3034) 
(list 1034.585 -210.1264) 
(list 960.5625 -199.04)))
(apply 'command (append '("pline") coords '("c")))
(setq currobj (ssadd (entlast) currobj))
(setq coords (list 
(list 960.5625 -198.897) 
(list 1034.585 -209.9834) 
(list 1034.585 -209.8064) 
(list 960.5625 -198.82)))
(apply 'command (append '("pline") coords '("c")))
(setq currobj (ssadd (entlast) currobj))
(setq coords (list 
(list 960.5625 -198.677) 
(list 1034.585 -209.6634) 
(list 1034.585 -209.4864) 
(list 960.5625 -198.6)))
(apply 'command (append '("pline") coords '("c")))
(setq currobj (ssadd (entlast) currobj))
(setq coords (list 
(list 960.5625 -198.457) 
(list 1034.585 -209.3434) 
(list 1034.585 -209.1664) 
(list 960.5625 -198.38)))
(apply 'command (append '("pline") coords '("c")))
(setq currobj (ssadd (entlast) currobj))
(setq coords (list 
(list 960.5625 -198.237) 
(list 1034.585 -209.0234) 
(list 1034.585 -208.8464) 
(list 960.5625 -198.16)))
(apply 'command (append '("pline") coords '("c")))
(setq currobj (ssadd (entlast) currobj))
(setq coords (list 
(list 960.5625 -198.017) 
(list 1034.585 -208.7034) 
(list 1034.585 -208.5264) 
(list 960.5625 -197.94)))
(apply 'command (append '("pline") coords '("c")))
(setq currobj (ssadd (entlast) currobj))
(setq coords (list 
(list 960.5625 -197.797) 
(list 1034.585 -208.3834) 
(list 1034.585 -208.2064) 
(list 960.5625 -197.72)))
(apply 'command (append '("pline") coords '("c")))
(setq currobj (ssadd (entlast) currobj))
(setq coords (list 
(list 960.5625 -197.577) 
(list 1034.585 -208.0634) 
(list 1034.585 -207.8864) 
(list 960.5625 -197.5)))
(apply 'command (append '("pline") coords '("c")))
(setq currobj (ssadd (entlast) currobj))
(setq coords (list 
(list 959.4375 -197.5) 
(list 885.415 -207.8864) 
(list 885.415 -208.0634) 
(list 959.4375 -197.577)))
(apply 'command (append '("pline") coords '("c")))
(setq currobj (ssadd (entlast) currobj))
(setq coords (list 
(list 959.4375 -197.72) 
(list 885.415 -208.2064) 
(list 885.415 -208.3834) 
(list 959.4375 -197.797)))
(apply 'command (append '("pline") coords '("c")))
(setq currobj (ssadd (entlast) currobj))
(setq coords (list 
(list 959.4375 -197.94) 
(list 885.415 -208.5264) 
(list 885.415 -208.7034) 
(list 959.4375 -198.017)))
(apply 'command (append '("pline") coords '("c")))
(setq currobj (ssadd (entlast) currobj))
(setq coords (list 
(list 959.4375 -198.16) 
(list 885.415 -208.8464) 
(list 885.415 -209.0234) 
(list 959.4375 -198.237)))
(apply 'command (append '("pline") coords '("c")))
(setq currobj (ssadd (entlast) currobj))
(setq coords (list 
(list 959.4375 -198.38) 
(list 885.415 -209.1664) 
(list 885.415 -209.3434) 
(list 959.4375 -198.457)))
(apply 'command (append '("pline") coords '("c")))
(setq currobj (ssadd (entlast) currobj))
(setq coords (list 
(list 959.4375 -198.6) 
(list 885.415 -209.4864) 
(list 885.415 -209.6634) 
(list 959.4375 -198.677)))
(apply 'command (append '("pline") coords '("c")))
(setq currobj (ssadd (entlast) currobj))
(setq coords (list 
(list 959.4375 -198.82) 
(list 885.415 -209.8064) 
(list 885.415 -209.9834) 
(list 959.4375 -198.897)))
(apply 'command (append '("pline") coords '("c")))
(setq currobj (ssadd (entlast) currobj))
(setq coords (list 
(list 959.4375 -199.04) 
(list 885.415 -210.1264) 
(list 885.415 -210.3034) 
(list 959.4375 -199.117)))
(apply 'command (append '("pline") coords '("c")))
(setq currobj (ssadd (entlast) currobj))
(setq coords (list 
(list 959.4375 -199.26) 
(list 885.415 -210.4464) 
(list 885.415 -210.6234) 
(list 959.4375 -199.337)))
(apply 'command (append '("pline") coords '("c")))
(setq currobj (ssadd (entlast) currobj))
(setq coords (list 
(list 959.4375 -199.48) 
(list 885.415 -210.7664) 
(list 885.415 -210.9434) 
(list 959.4375 -199.557)))
(apply 'command (append '("pline") coords '("c")))
(setq currobj (ssadd (entlast) currobj))
(setq coords (list 
(list 959.4375 -199.7) 
(list 885.415 -211.0864) 
(list 885.415 -211.2634) 
(list 959.4375 -199.777)))
(apply 'command (append '("pline") coords '("c")))
(setq currobj (ssadd (entlast) currobj))
(setq coords (list 
(list 959.4375 -199.92) 
(list 885.415 -211.4064) 
(list 885.415 -211.5834) 
(list 959.4375 -199.997)))
(apply 'command (append '("pline") coords '("c")))
(setq currobj (ssadd (entlast) currobj))
(setq coords (list 
(list 959.4375 -200.14) 
(list 885.415 -211.7264) 
(list 885.415 -211.9034) 
(list 959.4375 -200.217)))
(apply 'command (append '("pline") coords '("c")))
(setq currobj (ssadd (entlast) currobj))
(setq coords (list 
(list 959.4375 -200.36) 
(list 885.415 -212.0464) 
(list 885.415 -212.2234) 
(list 959.4375 -200.437)))
(apply 'command (append '("pline") coords '("c")))
(setq currobj (ssadd (entlast) currobj))
(setq coords (list 
(list 959.4375 -200.58) 
(list 885.415 -212.3664) 
(list 885.415 -212.5434) 
(list 959.4375 -200.657)))
(apply 'command (append '("pline") coords '("c")))
(setq currobj (ssadd (entlast) currobj))
(command "_layer" "set" "nitride" "")
(command "_layer" "set" "text" "")
(command "_circle" "958.985,-211.8" "0.075")
(command "_circle" "958.985,-211.5" "0.075")
(command "_circle" "958.985,-211.2" "0.075")
(command "_circle" "958.985,-210.9" "0.075")
(command "_circle" "958.985,-210.6" "0.075")
(command "_circle" "958.685,-211.8" "0.075")
(command "_circle" "958.685,-211.5" "0.075")
(command "_circle" "958.685,-211.2" "0.075")
(command "_circle" "958.685,-210.9" "0.075")
(command "_circle" "958.685,-210.6" "0.075")
(command "_circle" "958.385,-211.8" "0.075")
(command "_circle" "958.385,-211.5" "0.075")
(command "_circle" "958.385,-211.2" "0.075")
(command "_circle" "958.385,-210.9" "0.075")
(command "_circle" "958.385,-210.6" "0.075")
(command "_circle" "958.085,-211.8" "0.075")
(command "_circle" "958.085,-211.5" "0.075")
(command "_circle" "958.085,-211.2" "0.075")
(command "_circle" "958.085,-210.9" "0.075")
(command "_circle" "958.085,-210.6" "0.075")
(command "_circle" "957.785,-211.8" "0.075")
(command "_circle" "957.785,-211.5" "0.075")
(command "_circle" "957.785,-211.2" "0.075")
(command "_circle" "957.785,-210.9" "0.075")
(command "_circle" "957.785,-210.6" "0.075")
(command "_layer" "set" "nitride" "")
(setq anglednodearray3 currobj)
(setq currobj nil)
(setq currobj (ssadd))
; DRAWING COOLED SINGLE NANOBEAM
(setq coords (list 
(list 960.2625 -186.357) 
(list 960.2625 -181.357) 
(list 959.7375 -181.357) 
(list 959.7375 -186.357)))
(apply 'command (append '("pline") coords '("c")))
(setq currobj (ssadd (entlast) currobj))
(command "_layer" "set" "prebias" "")
(command "_rectangle" "959.7375,-186.357" "960.2625,-181.357")
(setq currobj (ssadd (entlast) currobj))
(command "_layer" "set" "nitride" "")
(setq coords (list 
(list 960.2625 -181.357) 
(list 960.5625 -171.357) 
(list 960.5625 -171.357) 
(list 960.5625 -170.357) 
(list 1034.585 -171.107) 
(list 1034.585 -166.164) 
(list 960.5625 -166.914) 
(list 960.5625 -165.914) 
(list 960.5625 -165.914) 
(list 960.2625 -155.914) 
(list 959.7375 -155.914) 
(list 959.4375 -165.914) 
(list 959.4375 -165.914) 
(list 959.4375 -166.914) 
(list 885.415 -166.164) 
(list 885.415 -171.107) 
(list 959.4375 -170.357) 
(list 959.4375 -171.357) 
(list 959.4375 -171.357) 
(list 959.7375 -181.357)))
(apply 'command (append '("pline") coords '("c")))
(setq currobj (ssadd (entlast) currobj))
(command "_layer" "set" "prebias" "")
(setq coords (list 
(list 959.4375 -181.357) 
(list 959.4375 -170.357) 
(list 885.415 -171.107) 
(list 885.415 -166.164) 
(list 959.4375 -166.914) 
(list 959.4375 -155.914) 
(list 960.5625 -155.914) 
(list 960.5625 -166.914) 
(list 1034.585 -166.164) 
(list 1034.585 -171.107) 
(list 960.5625 -170.357) 
(list 960.5625 -181.357)))
(apply 'command (append '("pline") coords '("c")))
(setq currobj (ssadd (entlast) currobj))
(command "_layer" "set" "nitride" "")
(command "_layer" "set" "fda1" "")
(setq coords (list 
(list 960.5625 -170.214) 
(list 1034.585 -170.964) 
(list 1034.585 -170.787) 
(list 960.5625 -170.137)))
(apply 'command (append '("pline") coords '("c")))
(setq currobj (ssadd (entlast) currobj))
(setq coords (list 
(list 960.5625 -169.994) 
(list 1034.585 -170.644) 
(list 1034.585 -170.467) 
(list 960.5625 -169.917)))
(apply 'command (append '("pline") coords '("c")))
(setq currobj (ssadd (entlast) currobj))
(setq coords (list 
(list 960.5625 -169.774) 
(list 1034.585 -170.324) 
(list 1034.585 -170.147) 
(list 960.5625 -169.697)))
(apply 'command (append '("pline") coords '("c")))
(setq currobj (ssadd (entlast) currobj))
(setq coords (list 
(list 960.5625 -169.554) 
(list 1034.585 -170.004) 
(list 1034.585 -169.827) 
(list 960.5625 -169.477)))
(apply 'command (append '("pline") coords '("c")))
(setq currobj (ssadd (entlast) currobj))
(setq coords (list 
(list 960.5625 -169.334) 
(list 1034.585 -169.684) 
(list 1034.585 -169.507) 
(list 960.5625 -169.257)))
(apply 'command (append '("pline") coords '("c")))
(setq currobj (ssadd (entlast) currobj))
(setq coords (list 
(list 960.5625 -169.114) 
(list 1034.585 -169.364) 
(list 1034.585 -169.187) 
(list 960.5625 -169.037)))
(apply 'command (append '("pline") coords '("c")))
(setq currobj (ssadd (entlast) currobj))
(setq coords (list 
(list 960.5625 -168.894) 
(list 1034.585 -169.044) 
(list 1034.585 -168.867) 
(list 960.5625 -168.817)))
(apply 'command (append '("pline") coords '("c")))
(setq currobj (ssadd (entlast) currobj))
(setq coords (list 
(list 960.5625 -168.674) 
(list 1034.585 -168.724) 
(list 1034.585 -168.547) 
(list 960.5625 -168.597)))
(apply 'command (append '("pline") coords '("c")))
(setq currobj (ssadd (entlast) currobj))
(setq coords (list 
(list 960.5625 -168.454) 
(list 1034.585 -168.404) 
(list 1034.585 -168.227) 
(list 960.5625 -168.377)))
(apply 'command (append '("pline") coords '("c")))
(setq currobj (ssadd (entlast) currobj))
(setq coords (list 
(list 960.5625 -168.234) 
(list 1034.585 -168.084) 
(list 1034.585 -167.907) 
(list 960.5625 -168.157)))
(apply 'command (append '("pline") coords '("c")))
(setq currobj (ssadd (entlast) currobj))
(setq coords (list 
(list 960.5625 -168.014) 
(list 1034.585 -167.764) 
(list 1034.585 -167.587) 
(list 960.5625 -167.937)))
(apply 'command (append '("pline") coords '("c")))
(setq currobj (ssadd (entlast) currobj))
(setq coords (list 
(list 960.5625 -167.794) 
(list 1034.585 -167.444) 
(list 1034.585 -167.267) 
(list 960.5625 -167.717)))
(apply 'command (append '("pline") coords '("c")))
(setq currobj (ssadd (entlast) currobj))
(setq coords (list 
(list 960.5625 -167.574) 
(list 1034.585 -167.124) 
(list 1034.585 -166.947) 
(list 960.5625 -167.497)))
(apply 'command (append '("pline") coords '("c")))
(setq currobj (ssadd (entlast) currobj))
(setq coords (list 
(list 960.5625 -167.354) 
(list 1034.585 -166.804) 
(list 1034.585 -166.627) 
(list 960.5625 -167.277)))
(apply 'command (append '("pline") coords '("c")))
(setq currobj (ssadd (entlast) currobj))
(setq coords (list 
(list 960.5625 -167.134) 
(list 1034.585 -166.484) 
(list 1034.585 -166.307) 
(list 960.5625 -167.057)))
(apply 'command (append '("pline") coords '("c")))
(setq currobj (ssadd (entlast) currobj))
(setq coords (list 
(list 959.4375 -167.057) 
(list 885.415 -166.307) 
(list 885.415 -166.484) 
(list 959.4375 -167.134)))
(apply 'command (append '("pline") coords '("c")))
(setq currobj (ssadd (entlast) currobj))
(setq coords (list 
(list 959.4375 -167.277) 
(list 885.415 -166.627) 
(list 885.415 -166.804) 
(list 959.4375 -167.354)))
(apply 'command (append '("pline") coords '("c")))
(setq currobj (ssadd (entlast) currobj))
(setq coords (list 
(list 959.4375 -167.497) 
(list 885.415 -166.947) 
(list 885.415 -167.124) 
(list 959.4375 -167.574)))
(apply 'command (append '("pline") coords '("c")))
(setq currobj (ssadd (entlast) currobj))
(setq coords (list 
(list 959.4375 -167.717) 
(list 885.415 -167.267) 
(list 885.415 -167.444) 
(list 959.4375 -167.794)))
(apply 'command (append '("pline") coords '("c")))
(setq currobj (ssadd (entlast) currobj))
(setq coords (list 
(list 959.4375 -167.937) 
(list 885.415 -167.587) 
(list 885.415 -167.764) 
(list 959.4375 -168.014)))
(apply 'command (append '("pline") coords '("c")))
(setq currobj (ssadd (entlast) currobj))
(setq coords (list 
(list 959.4375 -168.157) 
(list 885.415 -167.907) 
(list 885.415 -168.084) 
(list 959.4375 -168.234)))
(apply 'command (append '("pline") coords '("c")))
(setq currobj (ssadd (entlast) currobj))
(setq coords (list 
(list 959.4375 -168.377) 
(list 885.415 -168.227) 
(list 885.415 -168.404) 
(list 959.4375 -168.454)))
(apply 'command (append '("pline") coords '("c")))
(setq currobj (ssadd (entlast) currobj))
(setq coords (list 
(list 959.4375 -168.597) 
(list 885.415 -168.547) 
(list 885.415 -168.724) 
(list 959.4375 -168.674)))
(apply 'command (append '("pline") coords '("c")))
(setq currobj (ssadd (entlast) currobj))
(setq coords (list 
(list 959.4375 -168.817) 
(list 885.415 -168.867) 
(list 885.415 -169.044) 
(list 959.4375 -168.894)))
(apply 'command (append '("pline") coords '("c")))
(setq currobj (ssadd (entlast) currobj))
(setq coords (list 
(list 959.4375 -169.037) 
(list 885.415 -169.187) 
(list 885.415 -169.364) 
(list 959.4375 -169.114)))
(apply 'command (append '("pline") coords '("c")))
(setq currobj (ssadd (entlast) currobj))
(setq coords (list 
(list 959.4375 -169.257) 
(list 885.415 -169.507) 
(list 885.415 -169.684) 
(list 959.4375 -169.334)))
(apply 'command (append '("pline") coords '("c")))
(setq currobj (ssadd (entlast) currobj))
(setq coords (list 
(list 959.4375 -169.477) 
(list 885.415 -169.827) 
(list 885.415 -170.004) 
(list 959.4375 -169.554)))
(apply 'command (append '("pline") coords '("c")))
(setq currobj (ssadd (entlast) currobj))
(setq coords (list 
(list 959.4375 -169.697) 
(list 885.415 -170.147) 
(list 885.415 -170.324) 
(list 959.4375 -169.774)))
(apply 'command (append '("pline") coords '("c")))
(setq currobj (ssadd (entlast) currobj))
(setq coords (list 
(list 959.4375 -169.917) 
(list 885.415 -170.467) 
(list 885.415 -170.644) 
(list 959.4375 -169.994)))
(apply 'command (append '("pline") coords '("c")))
(setq currobj (ssadd (entlast) currobj))
(setq coords (list 
(list 959.4375 -170.137) 
(list 885.415 -170.787) 
(list 885.415 -170.964) 
(list 959.4375 -170.214)))
(apply 'command (append '("pline") coords '("c")))
(setq currobj (ssadd (entlast) currobj))
(command "_layer" "set" "nitride" "")
(command "_layer" "set" "text" "")
(command "_circle" "959.0625,-181.357" "0.075")
(command "_circle" "959.0625,-181.057" "0.075")
(command "_circle" "959.0625,-180.757" "0.075")
(command "_circle" "959.0625,-180.457" "0.075")
(command "_circle" "959.0625,-180.157" "0.075")
(command "_circle" "958.7625,-181.357" "0.075")
(command "_circle" "958.7625,-181.057" "0.075")
(command "_circle" "958.7625,-180.757" "0.075")
(command "_circle" "958.7625,-180.457" "0.075")
(command "_circle" "958.7625,-180.157" "0.075")
(command "_circle" "958.4625,-181.357" "0.075")
(command "_circle" "958.4625,-181.057" "0.075")
(command "_circle" "958.4625,-180.757" "0.075")
(command "_circle" "958.4625,-180.457" "0.075")
(command "_circle" "958.4625,-180.157" "0.075")
(command "_circle" "958.1625,-181.357" "0.075")
(command "_circle" "958.1625,-181.057" "0.075")
(command "_circle" "958.1625,-180.757" "0.075")
(command "_circle" "958.1625,-180.457" "0.075")
(command "_circle" "958.1625,-180.157" "0.075")
(command "_circle" "957.8625,-181.357" "0.075")
(command "_circle" "957.8625,-181.057" "0.075")
(command "_circle" "957.8625,-180.757" "0.075")
(command "_circle" "957.8625,-180.457" "0.075")
(command "_circle" "957.8625,-180.157" "0.075")
(command "_layer" "set" "nitride" "")
(setq coords (list 
(list 960.2625 -155.914) 
(list 960.2625 -40.2693) 
(list 959.7375 -40.2693) 
(list 959.7375 -155.914)))
(apply 'command (append '("pline") coords '("c")))
(setq currobj (ssadd (entlast) currobj))
(command "_layer" "set" "prebias" "")
(command "_rectangle" "959.7375,-155.914" "960.2625,-40.2693")
(setq currobj (ssadd (entlast) currobj))
(command "_layer" "set" "nitride" "")
(setq coords (list 
(list 960.2625 -40.2693) 
(list 960.5625 -30.2693) 
(list 960.5625 -30.2693) 
(list 960.5625 -29.2693) 
(list 1034.585 -30.0193) 
(list 1034.585 -25.0763) 
(list 960.5625 -25.8263) 
(list 960.5625 -24.8263) 
(list 960.5625 -24.8263) 
(list 960.2625 -14.8263) 
(list 959.7375 -14.8263) 
(list 959.4375 -24.8263) 
(list 959.4375 -24.8263) 
(list 959.4375 -25.8263) 
(list 885.415 -25.0763) 
(list 885.415 -30.0193) 
(list 959.4375 -29.2693) 
(list 959.4375 -30.2693) 
(list 959.4375 -30.2693) 
(list 959.7375 -40.2693)))
(apply 'command (append '("pline") coords '("c")))
(setq currobj (ssadd (entlast) currobj))
(command "_layer" "set" "prebias" "")
(setq coords (list 
(list 959.4375 -40.2693) 
(list 959.4375 -29.2693) 
(list 885.415 -30.0193) 
(list 885.415 -25.0763) 
(list 959.4375 -25.8263) 
(list 959.4375 -14.8263) 
(list 960.5625 -14.8263) 
(list 960.5625 -25.8263) 
(list 1034.585 -25.0763) 
(list 1034.585 -30.0193) 
(list 960.5625 -29.2693) 
(list 960.5625 -40.2693)))
(apply 'command (append '("pline") coords '("c")))
(setq currobj (ssadd (entlast) currobj))
(command "_layer" "set" "nitride" "")
(command "_layer" "set" "fda1" "")
(setq coords (list 
(list 960.5625 -29.1263) 
(list 1034.585 -29.8763) 
(list 1034.585 -29.6993) 
(list 960.5625 -29.0493)))
(apply 'command (append '("pline") coords '("c")))
(setq currobj (ssadd (entlast) currobj))
(setq coords (list 
(list 960.5625 -28.9063) 
(list 1034.585 -29.5563) 
(list 1034.585 -29.3793) 
(list 960.5625 -28.8293)))
(apply 'command (append '("pline") coords '("c")))
(setq currobj (ssadd (entlast) currobj))
(setq coords (list 
(list 960.5625 -28.6863) 
(list 1034.585 -29.2363) 
(list 1034.585 -29.0593) 
(list 960.5625 -28.6093)))
(apply 'command (append '("pline") coords '("c")))
(setq currobj (ssadd (entlast) currobj))
(setq coords (list 
(list 960.5625 -28.4663) 
(list 1034.585 -28.9163) 
(list 1034.585 -28.7393) 
(list 960.5625 -28.3893)))
(apply 'command (append '("pline") coords '("c")))
(setq currobj (ssadd (entlast) currobj))
(setq coords (list 
(list 960.5625 -28.2463) 
(list 1034.585 -28.5963) 
(list 1034.585 -28.4193) 
(list 960.5625 -28.1693)))
(apply 'command (append '("pline") coords '("c")))
(setq currobj (ssadd (entlast) currobj))
(setq coords (list 
(list 960.5625 -28.0263) 
(list 1034.585 -28.2763) 
(list 1034.585 -28.0993) 
(list 960.5625 -27.9493)))
(apply 'command (append '("pline") coords '("c")))
(setq currobj (ssadd (entlast) currobj))
(setq coords (list 
(list 960.5625 -27.8063) 
(list 1034.585 -27.9563) 
(list 1034.585 -27.7793) 
(list 960.5625 -27.7293)))
(apply 'command (append '("pline") coords '("c")))
(setq currobj (ssadd (entlast) currobj))
(setq coords (list 
(list 960.5625 -27.5863) 
(list 1034.585 -27.6363) 
(list 1034.585 -27.4593) 
(list 960.5625 -27.5093)))
(apply 'command (append '("pline") coords '("c")))
(setq currobj (ssadd (entlast) currobj))
(setq coords (list 
(list 960.5625 -27.3663) 
(list 1034.585 -27.3163) 
(list 1034.585 -27.1393) 
(list 960.5625 -27.2893)))
(apply 'command (append '("pline") coords '("c")))
(setq currobj (ssadd (entlast) currobj))
(setq coords (list 
(list 960.5625 -27.1463) 
(list 1034.585 -26.9963) 
(list 1034.585 -26.8193) 
(list 960.5625 -27.0693)))
(apply 'command (append '("pline") coords '("c")))
(setq currobj (ssadd (entlast) currobj))
(setq coords (list 
(list 960.5625 -26.9263) 
(list 1034.585 -26.6763) 
(list 1034.585 -26.4993) 
(list 960.5625 -26.8493)))
(apply 'command (append '("pline") coords '("c")))
(setq currobj (ssadd (entlast) currobj))
(setq coords (list 
(list 960.5625 -26.7063) 
(list 1034.585 -26.3563) 
(list 1034.585 -26.1793) 
(list 960.5625 -26.6293)))
(apply 'command (append '("pline") coords '("c")))
(setq currobj (ssadd (entlast) currobj))
(setq coords (list 
(list 960.5625 -26.4863) 
(list 1034.585 -26.0363) 
(list 1034.585 -25.8593) 
(list 960.5625 -26.4093)))
(apply 'command (append '("pline") coords '("c")))
(setq currobj (ssadd (entlast) currobj))
(setq coords (list 
(list 960.5625 -26.2663) 
(list 1034.585 -25.7163) 
(list 1034.585 -25.5393) 
(list 960.5625 -26.1893)))
(apply 'command (append '("pline") coords '("c")))
(setq currobj (ssadd (entlast) currobj))
(setq coords (list 
(list 960.5625 -26.0463) 
(list 1034.585 -25.3963) 
(list 1034.585 -25.2193) 
(list 960.5625 -25.9693)))
(apply 'command (append '("pline") coords '("c")))
(setq currobj (ssadd (entlast) currobj))
(setq coords (list 
(list 959.4375 -25.9693) 
(list 885.415 -25.2193) 
(list 885.415 -25.3963) 
(list 959.4375 -26.0463)))
(apply 'command (append '("pline") coords '("c")))
(setq currobj (ssadd (entlast) currobj))
(setq coords (list 
(list 959.4375 -26.1893) 
(list 885.415 -25.5393) 
(list 885.415 -25.7163) 
(list 959.4375 -26.2663)))
(apply 'command (append '("pline") coords '("c")))
(setq currobj (ssadd (entlast) currobj))
(setq coords (list 
(list 959.4375 -26.4093) 
(list 885.415 -25.8593) 
(list 885.415 -26.0363) 
(list 959.4375 -26.4863)))
(apply 'command (append '("pline") coords '("c")))
(setq currobj (ssadd (entlast) currobj))
(setq coords (list 
(list 959.4375 -26.6293) 
(list 885.415 -26.1793) 
(list 885.415 -26.3563) 
(list 959.4375 -26.7063)))
(apply 'command (append '("pline") coords '("c")))
(setq currobj (ssadd (entlast) currobj))
(setq coords (list 
(list 959.4375 -26.8493) 
(list 885.415 -26.4993) 
(list 885.415 -26.6763) 
(list 959.4375 -26.9263)))
(apply 'command (append '("pline") coords '("c")))
(setq currobj (ssadd (entlast) currobj))
(setq coords (list 
(list 959.4375 -27.0693) 
(list 885.415 -26.8193) 
(list 885.415 -26.9963) 
(list 959.4375 -27.1463)))
(apply 'command (append '("pline") coords '("c")))
(setq currobj (ssadd (entlast) currobj))
(setq coords (list 
(list 959.4375 -27.2893) 
(list 885.415 -27.1393) 
(list 885.415 -27.3163) 
(list 959.4375 -27.3663)))
(apply 'command (append '("pline") coords '("c")))
(setq currobj (ssadd (entlast) currobj))
(setq coords (list 
(list 959.4375 -27.5093) 
(list 885.415 -27.4593) 
(list 885.415 -27.6363) 
(list 959.4375 -27.5863)))
(apply 'command (append '("pline") coords '("c")))
(setq currobj (ssadd (entlast) currobj))
(setq coords (list 
(list 959.4375 -27.7293) 
(list 885.415 -27.7793) 
(list 885.415 -27.9563) 
(list 959.4375 -27.8063)))
(apply 'command (append '("pline") coords '("c")))
(setq currobj (ssadd (entlast) currobj))
(setq coords (list 
(list 959.4375 -27.9493) 
(list 885.415 -28.0993) 
(list 885.415 -28.2763) 
(list 959.4375 -28.0263)))
(apply 'command (append '("pline") coords '("c")))
(setq currobj (ssadd (entlast) currobj))
(setq coords (list 
(list 959.4375 -28.1693) 
(list 885.415 -28.4193) 
(list 885.415 -28.5963) 
(list 959.4375 -28.2463)))
(apply 'command (append '("pline") coords '("c")))
(setq currobj (ssadd (entlast) currobj))
(setq coords (list 
(list 959.4375 -28.3893) 
(list 885.415 -28.7393) 
(list 885.415 -28.9163) 
(list 959.4375 -28.4663)))
(apply 'command (append '("pline") coords '("c")))
(setq currobj (ssadd (entlast) currobj))
(setq coords (list 
(list 959.4375 -28.6093) 
(list 885.415 -29.0593) 
(list 885.415 -29.2363) 
(list 959.4375 -28.6863)))
(apply 'command (append '("pline") coords '("c")))
(setq currobj (ssadd (entlast) currobj))
(setq coords (list 
(list 959.4375 -28.8293) 
(list 885.415 -29.3793) 
(list 885.415 -29.5563) 
(list 959.4375 -28.9063)))
(apply 'command (append '("pline") coords '("c")))
(setq currobj (ssadd (entlast) currobj))
(setq coords (list 
(list 959.4375 -29.0493) 
(list 885.415 -29.6993) 
(list 885.415 -29.8763) 
(list 959.4375 -29.1263)))
(apply 'command (append '("pline") coords '("c")))
(setq currobj (ssadd (entlast) currobj))
(command "_layer" "set" "nitride" "")
(command "_layer" "set" "text" "")
(command "_circle" "959.0625,-40.2693" "0.075")
(command "_circle" "959.0625,-39.9693" "0.075")
(command "_circle" "959.0625,-39.6693" "0.075")
(command "_circle" "959.0625,-39.3693" "0.075")
(command "_circle" "959.0625,-39.0693" "0.075")
(command "_circle" "958.7625,-40.2693" "0.075")
(command "_circle" "958.7625,-39.9693" "0.075")
(command "_circle" "958.7625,-39.6693" "0.075")
(command "_circle" "958.7625,-39.3693" "0.075")
(command "_circle" "958.7625,-39.0693" "0.075")
(command "_circle" "958.4625,-40.2693" "0.075")
(command "_circle" "958.4625,-39.9693" "0.075")
(command "_circle" "958.4625,-39.6693" "0.075")
(command "_circle" "958.4625,-39.3693" "0.075")
(command "_circle" "958.4625,-39.0693" "0.075")
(command "_circle" "958.1625,-40.2693" "0.075")
(command "_circle" "958.1625,-39.9693" "0.075")
(command "_circle" "958.1625,-39.6693" "0.075")
(command "_circle" "958.1625,-39.3693" "0.075")
(command "_circle" "958.1625,-39.0693" "0.075")
(command "_circle" "957.8625,-40.2693" "0.075")
(command "_circle" "957.8625,-39.9693" "0.075")
(command "_circle" "957.8625,-39.6693" "0.075")
(command "_circle" "957.8625,-39.3693" "0.075")
(command "_circle" "957.8625,-39.0693" "0.075")
(command "_layer" "set" "nitride" "")
(setq coords (list 
(list 960.2625 -14.8263) 
(list 960.2625 100.8184) 
(list 959.7375 100.8184) 
(list 959.7375 -14.8263)))
(apply 'command (append '("pline") coords '("c")))
(setq currobj (ssadd (entlast) currobj))
(command "_layer" "set" "prebias" "")
(command "_rectangle" "959.7375,-14.8263" "960.2625,100.8184")
(setq currobj (ssadd (entlast) currobj))
(command "_layer" "set" "nitride" "")
(setq coords (list 
(list 960.2625 100.8184) 
(list 960.5625 110.8184) 
(list 960.5625 110.8184) 
(list 960.5625 111.8184) 
(list 1034.585 111.0684) 
(list 1034.585 116.0114) 
(list 960.5625 115.2614) 
(list 960.5625 116.2614) 
(list 960.5625 116.2614) 
(list 960.2625 126.2614) 
(list 959.7375 126.2614) 
(list 959.4375 116.2614) 
(list 959.4375 116.2614) 
(list 959.4375 115.2614) 
(list 885.415 116.0114) 
(list 885.415 111.0684) 
(list 959.4375 111.8184) 
(list 959.4375 110.8184) 
(list 959.4375 110.8184) 
(list 959.7375 100.8184)))
(apply 'command (append '("pline") coords '("c")))
(setq currobj (ssadd (entlast) currobj))
(command "_layer" "set" "prebias" "")
(setq coords (list 
(list 959.4375 100.8184) 
(list 959.4375 111.8184) 
(list 885.415 111.0684) 
(list 885.415 116.0114) 
(list 959.4375 115.2614) 
(list 959.4375 126.2614) 
(list 960.5625 126.2614) 
(list 960.5625 115.2614) 
(list 1034.585 116.0114) 
(list 1034.585 111.0684) 
(list 960.5625 111.8184) 
(list 960.5625 100.8184)))
(apply 'command (append '("pline") coords '("c")))
(setq currobj (ssadd (entlast) currobj))
(command "_layer" "set" "nitride" "")
(command "_layer" "set" "fda1" "")
(setq coords (list 
(list 960.5625 111.9614) 
(list 1034.585 111.2114) 
(list 1034.585 111.3884) 
(list 960.5625 112.0384)))
(apply 'command (append '("pline") coords '("c")))
(setq currobj (ssadd (entlast) currobj))
(setq coords (list 
(list 960.5625 112.1814) 
(list 1034.585 111.5314) 
(list 1034.585 111.7084) 
(list 960.5625 112.2584)))
(apply 'command (append '("pline") coords '("c")))
(setq currobj (ssadd (entlast) currobj))
(setq coords (list 
(list 960.5625 112.4014) 
(list 1034.585 111.8514) 
(list 1034.585 112.0284) 
(list 960.5625 112.4784)))
(apply 'command (append '("pline") coords '("c")))
(setq currobj (ssadd (entlast) currobj))
(setq coords (list 
(list 960.5625 112.6214) 
(list 1034.585 112.1714) 
(list 1034.585 112.3484) 
(list 960.5625 112.6984)))
(apply 'command (append '("pline") coords '("c")))
(setq currobj (ssadd (entlast) currobj))
(setq coords (list 
(list 960.5625 112.8414) 
(list 1034.585 112.4914) 
(list 1034.585 112.6684) 
(list 960.5625 112.9184)))
(apply 'command (append '("pline") coords '("c")))
(setq currobj (ssadd (entlast) currobj))
(setq coords (list 
(list 960.5625 113.0614) 
(list 1034.585 112.8114) 
(list 1034.585 112.9884) 
(list 960.5625 113.1384)))
(apply 'command (append '("pline") coords '("c")))
(setq currobj (ssadd (entlast) currobj))
(setq coords (list 
(list 960.5625 113.2814) 
(list 1034.585 113.1314) 
(list 1034.585 113.3084) 
(list 960.5625 113.3584)))
(apply 'command (append '("pline") coords '("c")))
(setq currobj (ssadd (entlast) currobj))
(setq coords (list 
(list 960.5625 113.5014) 
(list 1034.585 113.4514) 
(list 1034.585 113.6284) 
(list 960.5625 113.5784)))
(apply 'command (append '("pline") coords '("c")))
(setq currobj (ssadd (entlast) currobj))
(setq coords (list 
(list 960.5625 113.7214) 
(list 1034.585 113.7714) 
(list 1034.585 113.9484) 
(list 960.5625 113.7984)))
(apply 'command (append '("pline") coords '("c")))
(setq currobj (ssadd (entlast) currobj))
(setq coords (list 
(list 960.5625 113.9414) 
(list 1034.585 114.0914) 
(list 1034.585 114.2684) 
(list 960.5625 114.0184)))
(apply 'command (append '("pline") coords '("c")))
(setq currobj (ssadd (entlast) currobj))
(setq coords (list 
(list 960.5625 114.1614) 
(list 1034.585 114.4114) 
(list 1034.585 114.5884) 
(list 960.5625 114.2384)))
(apply 'command (append '("pline") coords '("c")))
(setq currobj (ssadd (entlast) currobj))
(setq coords (list 
(list 960.5625 114.3814) 
(list 1034.585 114.7314) 
(list 1034.585 114.9084) 
(list 960.5625 114.4584)))
(apply 'command (append '("pline") coords '("c")))
(setq currobj (ssadd (entlast) currobj))
(setq coords (list 
(list 960.5625 114.6014) 
(list 1034.585 115.0514) 
(list 1034.585 115.2284) 
(list 960.5625 114.6784)))
(apply 'command (append '("pline") coords '("c")))
(setq currobj (ssadd (entlast) currobj))
(setq coords (list 
(list 960.5625 114.8214) 
(list 1034.585 115.3714) 
(list 1034.585 115.5484) 
(list 960.5625 114.8984)))
(apply 'command (append '("pline") coords '("c")))
(setq currobj (ssadd (entlast) currobj))
(setq coords (list 
(list 960.5625 115.0414) 
(list 1034.585 115.6914) 
(list 1034.585 115.8684) 
(list 960.5625 115.1184)))
(apply 'command (append '("pline") coords '("c")))
(setq currobj (ssadd (entlast) currobj))
(setq coords (list 
(list 959.4375 115.1184) 
(list 885.415 115.8684) 
(list 885.415 115.6914) 
(list 959.4375 115.0414)))
(apply 'command (append '("pline") coords '("c")))
(setq currobj (ssadd (entlast) currobj))
(setq coords (list 
(list 959.4375 114.8984) 
(list 885.415 115.5484) 
(list 885.415 115.3714) 
(list 959.4375 114.8214)))
(apply 'command (append '("pline") coords '("c")))
(setq currobj (ssadd (entlast) currobj))
(setq coords (list 
(list 959.4375 114.6784) 
(list 885.415 115.2284) 
(list 885.415 115.0514) 
(list 959.4375 114.6014)))
(apply 'command (append '("pline") coords '("c")))
(setq currobj (ssadd (entlast) currobj))
(setq coords (list 
(list 959.4375 114.4584) 
(list 885.415 114.9084) 
(list 885.415 114.7314) 
(list 959.4375 114.3814)))
(apply 'command (append '("pline") coords '("c")))
(setq currobj (ssadd (entlast) currobj))
(setq coords (list 
(list 959.4375 114.2384) 
(list 885.415 114.5884) 
(list 885.415 114.4114) 
(list 959.4375 114.1614)))
(apply 'command (append '("pline") coords '("c")))
(setq currobj (ssadd (entlast) currobj))
(setq coords (list 
(list 959.4375 114.0184) 
(list 885.415 114.2684) 
(list 885.415 114.0914) 
(list 959.4375 113.9414)))
(apply 'command (append '("pline") coords '("c")))
(setq currobj (ssadd (entlast) currobj))
(setq coords (list 
(list 959.4375 113.7984) 
(list 885.415 113.9484) 
(list 885.415 113.7714) 
(list 959.4375 113.7214)))
(apply 'command (append '("pline") coords '("c")))
(setq currobj (ssadd (entlast) currobj))
(setq coords (list 
(list 959.4375 113.5784) 
(list 885.415 113.6284) 
(list 885.415 113.4514) 
(list 959.4375 113.5014)))
(apply 'command (append '("pline") coords '("c")))
(setq currobj (ssadd (entlast) currobj))
(setq coords (list 
(list 959.4375 113.3584) 
(list 885.415 113.3084) 
(list 885.415 113.1314) 
(list 959.4375 113.2814)))
(apply 'command (append '("pline") coords '("c")))
(setq currobj (ssadd (entlast) currobj))
(setq coords (list 
(list 959.4375 113.1384) 
(list 885.415 112.9884) 
(list 885.415 112.8114) 
(list 959.4375 113.0614)))
(apply 'command (append '("pline") coords '("c")))
(setq currobj (ssadd (entlast) currobj))
(setq coords (list 
(list 959.4375 112.9184) 
(list 885.415 112.6684) 
(list 885.415 112.4914) 
(list 959.4375 112.8414)))
(apply 'command (append '("pline") coords '("c")))
(setq currobj (ssadd (entlast) currobj))
(setq coords (list 
(list 959.4375 112.6984) 
(list 885.415 112.3484) 
(list 885.415 112.1714) 
(list 959.4375 112.6214)))
(apply 'command (append '("pline") coords '("c")))
(setq currobj (ssadd (entlast) currobj))
(setq coords (list 
(list 959.4375 112.4784) 
(list 885.415 112.0284) 
(list 885.415 111.8514) 
(list 959.4375 112.4014)))
(apply 'command (append '("pline") coords '("c")))
(setq currobj (ssadd (entlast) currobj))
(setq coords (list 
(list 959.4375 112.2584) 
(list 885.415 111.7084) 
(list 885.415 111.5314) 
(list 959.4375 112.1814)))
(apply 'command (append '("pline") coords '("c")))
(setq currobj (ssadd (entlast) currobj))
(setq coords (list 
(list 959.4375 112.0384) 
(list 885.415 111.3884) 
(list 885.415 111.2114) 
(list 959.4375 111.9614)))
(apply 'command (append '("pline") coords '("c")))
(setq currobj (ssadd (entlast) currobj))
(command "_layer" "set" "nitride" "")
(command "_layer" "set" "text" "")
(command "_circle" "959.0625,100.8184" "0.075")
(command "_circle" "959.0625,101.1184" "0.075")
(command "_circle" "959.0625,101.4184" "0.075")
(command "_circle" "959.0625,101.7184" "0.075")
(command "_circle" "959.0625,102.0184" "0.075")
(command "_circle" "958.7625,100.8184" "0.075")
(command "_circle" "958.7625,101.1184" "0.075")
(command "_circle" "958.7625,101.4184" "0.075")
(command "_circle" "958.7625,101.7184" "0.075")
(command "_circle" "958.7625,102.0184" "0.075")
(command "_circle" "958.4625,100.8184" "0.075")
(command "_circle" "958.4625,101.1184" "0.075")
(command "_circle" "958.4625,101.4184" "0.075")
(command "_circle" "958.4625,101.7184" "0.075")
(command "_circle" "958.4625,102.0184" "0.075")
(command "_circle" "958.1625,100.8184" "0.075")
(command "_circle" "958.1625,101.1184" "0.075")
(command "_circle" "958.1625,101.4184" "0.075")
(command "_circle" "958.1625,101.7184" "0.075")
(command "_circle" "958.1625,102.0184" "0.075")
(command "_circle" "957.8625,100.8184" "0.075")
(command "_circle" "957.8625,101.1184" "0.075")
(command "_circle" "957.8625,101.4184" "0.075")
(command "_circle" "957.8625,101.7184" "0.075")
(command "_circle" "957.8625,102.0184" "0.075")
(command "_layer" "set" "nitride" "")
(setq coords (list 
(list 960.2625 126.2614) 
(list 960.2625 241.9061) 
(list 959.7375 241.9061) 
(list 959.7375 126.2614)))
(apply 'command (append '("pline") coords '("c")))
(setq currobj (ssadd (entlast) currobj))
(command "_layer" "set" "prebias" "")
(command "_rectangle" "959.7375,126.2614" "960.2625,241.9061")
(setq currobj (ssadd (entlast) currobj))
(command "_layer" "set" "nitride" "")
(setq coords (list 
(list 960.2625 241.9061) 
(list 960.5625 251.9061) 
(list 960.5625 251.9061) 
(list 960.5625 252.9061) 
(list 1034.585 252.1561) 
(list 1034.585 257.0991) 
(list 960.5625 256.3491) 
(list 960.5625 257.3491) 
(list 960.5625 257.3491) 
(list 960.2625 267.3491) 
(list 959.7375 267.3491) 
(list 959.4375 257.3491) 
(list 959.4375 257.3491) 
(list 959.4375 256.3491) 
(list 885.415 257.0991) 
(list 885.415 252.1561) 
(list 959.4375 252.9061) 
(list 959.4375 251.9061) 
(list 959.4375 251.9061) 
(list 959.7375 241.9061)))
(apply 'command (append '("pline") coords '("c")))
(setq currobj (ssadd (entlast) currobj))
(command "_layer" "set" "prebias" "")
(setq coords (list 
(list 959.4375 241.9061) 
(list 959.4375 252.9061) 
(list 885.415 252.1561) 
(list 885.415 257.0991) 
(list 959.4375 256.3491) 
(list 959.4375 267.3491) 
(list 960.5625 267.3491) 
(list 960.5625 256.3491) 
(list 1034.585 257.0991) 
(list 1034.585 252.1561) 
(list 960.5625 252.9061) 
(list 960.5625 241.9061)))
(apply 'command (append '("pline") coords '("c")))
(setq currobj (ssadd (entlast) currobj))
(command "_layer" "set" "nitride" "")
(command "_layer" "set" "fda1" "")
(setq coords (list 
(list 960.5625 253.0491) 
(list 1034.585 252.2991) 
(list 1034.585 252.4761) 
(list 960.5625 253.1261)))
(apply 'command (append '("pline") coords '("c")))
(setq currobj (ssadd (entlast) currobj))
(setq coords (list 
(list 960.5625 253.2691) 
(list 1034.585 252.6191) 
(list 1034.585 252.7961) 
(list 960.5625 253.3461)))
(apply 'command (append '("pline") coords '("c")))
(setq currobj (ssadd (entlast) currobj))
(setq coords (list 
(list 960.5625 253.4891) 
(list 1034.585 252.9391) 
(list 1034.585 253.1161) 
(list 960.5625 253.5661)))
(apply 'command (append '("pline") coords '("c")))
(setq currobj (ssadd (entlast) currobj))
(setq coords (list 
(list 960.5625 253.7091) 
(list 1034.585 253.2591) 
(list 1034.585 253.4361) 
(list 960.5625 253.7861)))
(apply 'command (append '("pline") coords '("c")))
(setq currobj (ssadd (entlast) currobj))
(setq coords (list 
(list 960.5625 253.9291) 
(list 1034.585 253.5791) 
(list 1034.585 253.7561) 
(list 960.5625 254.0061)))
(apply 'command (append '("pline") coords '("c")))
(setq currobj (ssadd (entlast) currobj))
(setq coords (list 
(list 960.5625 254.1491) 
(list 1034.585 253.8991) 
(list 1034.585 254.0761) 
(list 960.5625 254.2261)))
(apply 'command (append '("pline") coords '("c")))
(setq currobj (ssadd (entlast) currobj))
(setq coords (list 
(list 960.5625 254.3691) 
(list 1034.585 254.2191) 
(list 1034.585 254.3961) 
(list 960.5625 254.4461)))
(apply 'command (append '("pline") coords '("c")))
(setq currobj (ssadd (entlast) currobj))
(setq coords (list 
(list 960.5625 254.5891) 
(list 1034.585 254.5391) 
(list 1034.585 254.7161) 
(list 960.5625 254.6661)))
(apply 'command (append '("pline") coords '("c")))
(setq currobj (ssadd (entlast) currobj))
(setq coords (list 
(list 960.5625 254.8091) 
(list 1034.585 254.8591) 
(list 1034.585 255.0361) 
(list 960.5625 254.8861)))
(apply 'command (append '("pline") coords '("c")))
(setq currobj (ssadd (entlast) currobj))
(setq coords (list 
(list 960.5625 255.0291) 
(list 1034.585 255.1791) 
(list 1034.585 255.3561) 
(list 960.5625 255.1061)))
(apply 'command (append '("pline") coords '("c")))
(setq currobj (ssadd (entlast) currobj))
(setq coords (list 
(list 960.5625 255.2491) 
(list 1034.585 255.4991) 
(list 1034.585 255.6761) 
(list 960.5625 255.3261)))
(apply 'command (append '("pline") coords '("c")))
(setq currobj (ssadd (entlast) currobj))
(setq coords (list 
(list 960.5625 255.4691) 
(list 1034.585 255.8191) 
(list 1034.585 255.9961) 
(list 960.5625 255.5461)))
(apply 'command (append '("pline") coords '("c")))
(setq currobj (ssadd (entlast) currobj))
(setq coords (list 
(list 960.5625 255.6891) 
(list 1034.585 256.1391) 
(list 1034.585 256.3161) 
(list 960.5625 255.7661)))
(apply 'command (append '("pline") coords '("c")))
(setq currobj (ssadd (entlast) currobj))
(setq coords (list 
(list 960.5625 255.9091) 
(list 1034.585 256.4591) 
(list 1034.585 256.6361) 
(list 960.5625 255.9861)))
(apply 'command (append '("pline") coords '("c")))
(setq currobj (ssadd (entlast) currobj))
(setq coords (list 
(list 960.5625 256.1291) 
(list 1034.585 256.7791) 
(list 1034.585 256.9561) 
(list 960.5625 256.2061)))
(apply 'command (append '("pline") coords '("c")))
(setq currobj (ssadd (entlast) currobj))
(setq coords (list 
(list 959.4375 256.2061) 
(list 885.415 256.9561) 
(list 885.415 256.7791) 
(list 959.4375 256.1291)))
(apply 'command (append '("pline") coords '("c")))
(setq currobj (ssadd (entlast) currobj))
(setq coords (list 
(list 959.4375 255.9861) 
(list 885.415 256.6361) 
(list 885.415 256.4591) 
(list 959.4375 255.9091)))
(apply 'command (append '("pline") coords '("c")))
(setq currobj (ssadd (entlast) currobj))
(setq coords (list 
(list 959.4375 255.7661) 
(list 885.415 256.3161) 
(list 885.415 256.1391) 
(list 959.4375 255.6891)))
(apply 'command (append '("pline") coords '("c")))
(setq currobj (ssadd (entlast) currobj))
(setq coords (list 
(list 959.4375 255.5461) 
(list 885.415 255.9961) 
(list 885.415 255.8191) 
(list 959.4375 255.4691)))
(apply 'command (append '("pline") coords '("c")))
(setq currobj (ssadd (entlast) currobj))
(setq coords (list 
(list 959.4375 255.3261) 
(list 885.415 255.6761) 
(list 885.415 255.4991) 
(list 959.4375 255.2491)))
(apply 'command (append '("pline") coords '("c")))
(setq currobj (ssadd (entlast) currobj))
(setq coords (list 
(list 959.4375 255.1061) 
(list 885.415 255.3561) 
(list 885.415 255.1791) 
(list 959.4375 255.0291)))
(apply 'command (append '("pline") coords '("c")))
(setq currobj (ssadd (entlast) currobj))
(setq coords (list 
(list 959.4375 254.8861) 
(list 885.415 255.0361) 
(list 885.415 254.8591) 
(list 959.4375 254.8091)))
(apply 'command (append '("pline") coords '("c")))
(setq currobj (ssadd (entlast) currobj))
(setq coords (list 
(list 959.4375 254.6661) 
(list 885.415 254.7161) 
(list 885.415 254.5391) 
(list 959.4375 254.5891)))
(apply 'command (append '("pline") coords '("c")))
(setq currobj (ssadd (entlast) currobj))
(setq coords (list 
(list 959.4375 254.4461) 
(list 885.415 254.3961) 
(list 885.415 254.2191) 
(list 959.4375 254.3691)))
(apply 'command (append '("pline") coords '("c")))
(setq currobj (ssadd (entlast) currobj))
(setq coords (list 
(list 959.4375 254.2261) 
(list 885.415 254.0761) 
(list 885.415 253.8991) 
(list 959.4375 254.1491)))
(apply 'command (append '("pline") coords '("c")))
(setq currobj (ssadd (entlast) currobj))
(setq coords (list 
(list 959.4375 254.0061) 
(list 885.415 253.7561) 
(list 885.415 253.5791) 
(list 959.4375 253.9291)))
(apply 'command (append '("pline") coords '("c")))
(setq currobj (ssadd (entlast) currobj))
(setq coords (list 
(list 959.4375 253.7861) 
(list 885.415 253.4361) 
(list 885.415 253.2591) 
(list 959.4375 253.7091)))
(apply 'command (append '("pline") coords '("c")))
(setq currobj (ssadd (entlast) currobj))
(setq coords (list 
(list 959.4375 253.5661) 
(list 885.415 253.1161) 
(list 885.415 252.9391) 
(list 959.4375 253.4891)))
(apply 'command (append '("pline") coords '("c")))
(setq currobj (ssadd (entlast) currobj))
(setq coords (list 
(list 959.4375 253.3461) 
(list 885.415 252.7961) 
(list 885.415 252.6191) 
(list 959.4375 253.2691)))
(apply 'command (append '("pline") coords '("c")))
(setq currobj (ssadd (entlast) currobj))
(setq coords (list 
(list 959.4375 253.1261) 
(list 885.415 252.4761) 
(list 885.415 252.2991) 
(list 959.4375 253.0491)))
(apply 'command (append '("pline") coords '("c")))
(setq currobj (ssadd (entlast) currobj))
(command "_layer" "set" "nitride" "")
(command "_layer" "set" "text" "")
(command "_circle" "959.0625,241.9061" "0.075")
(command "_circle" "959.0625,242.2061" "0.075")
(command "_circle" "959.0625,242.5061" "0.075")
(command "_circle" "959.0625,242.8061" "0.075")
(command "_circle" "959.0625,243.1061" "0.075")
(command "_circle" "958.7625,241.9061" "0.075")
(command "_circle" "958.7625,242.2061" "0.075")
(command "_circle" "958.7625,242.5061" "0.075")
(command "_circle" "958.7625,242.8061" "0.075")
(command "_circle" "958.7625,243.1061" "0.075")
(command "_circle" "958.4625,241.9061" "0.075")
(command "_circle" "958.4625,242.2061" "0.075")
(command "_circle" "958.4625,242.5061" "0.075")
(command "_circle" "958.4625,242.8061" "0.075")
(command "_circle" "958.4625,243.1061" "0.075")
(command "_circle" "958.1625,241.9061" "0.075")
(command "_circle" "958.1625,242.2061" "0.075")
(command "_circle" "958.1625,242.5061" "0.075")
(command "_circle" "958.1625,242.8061" "0.075")
(command "_circle" "958.1625,243.1061" "0.075")
(command "_circle" "957.8625,241.9061" "0.075")
(command "_circle" "957.8625,242.2061" "0.075")
(command "_circle" "957.8625,242.5061" "0.075")
(command "_circle" "957.8625,242.8061" "0.075")
(command "_circle" "957.8625,243.1061" "0.075")
(command "_layer" "set" "nitride" "")
(setq coords (list 
(list 960.2625 267.3491) 
(list 960.2625 382.9939) 
(list 959.7375 382.9939) 
(list 959.7375 267.3491)))
(apply 'command (append '("pline") coords '("c")))
(setq currobj (ssadd (entlast) currobj))
(command "_layer" "set" "prebias" "")
(command "_rectangle" "959.7375,267.3491" "960.2625,382.9939")
(setq currobj (ssadd (entlast) currobj))
(command "_layer" "set" "nitride" "")
(setq coords (list 
(list 960.2625 382.9939) 
(list 960.5625 392.9939) 
(list 960.5625 392.9939) 
(list 960.5625 393.9939) 
(list 1034.585 393.2439) 
(list 1034.585 398.1869) 
(list 960.5625 397.4369) 
(list 960.5625 398.4369) 
(list 960.5625 398.4369) 
(list 960.2625 408.4369) 
(list 959.7375 408.4369) 
(list 959.4375 398.4369) 
(list 959.4375 398.4369) 
(list 959.4375 397.4369) 
(list 885.415 398.1869) 
(list 885.415 393.2439) 
(list 959.4375 393.9939) 
(list 959.4375 392.9939) 
(list 959.4375 392.9939) 
(list 959.7375 382.9939)))
(apply 'command (append '("pline") coords '("c")))
(setq currobj (ssadd (entlast) currobj))
(command "_layer" "set" "prebias" "")
(setq coords (list 
(list 959.4375 382.9939) 
(list 959.4375 393.9939) 
(list 885.415 393.2439) 
(list 885.415 398.1869) 
(list 959.4375 397.4369) 
(list 959.4375 408.4369) 
(list 960.5625 408.4369) 
(list 960.5625 397.4369) 
(list 1034.585 398.1869) 
(list 1034.585 393.2439) 
(list 960.5625 393.9939) 
(list 960.5625 382.9939)))
(apply 'command (append '("pline") coords '("c")))
(setq currobj (ssadd (entlast) currobj))
(command "_layer" "set" "nitride" "")
(command "_layer" "set" "fda1" "")
(setq coords (list 
(list 960.5625 394.1369) 
(list 1034.585 393.3869) 
(list 1034.585 393.5639) 
(list 960.5625 394.2139)))
(apply 'command (append '("pline") coords '("c")))
(setq currobj (ssadd (entlast) currobj))
(setq coords (list 
(list 960.5625 394.3569) 
(list 1034.585 393.7069) 
(list 1034.585 393.8839) 
(list 960.5625 394.4339)))
(apply 'command (append '("pline") coords '("c")))
(setq currobj (ssadd (entlast) currobj))
(setq coords (list 
(list 960.5625 394.5769) 
(list 1034.585 394.0269) 
(list 1034.585 394.2039) 
(list 960.5625 394.6539)))
(apply 'command (append '("pline") coords '("c")))
(setq currobj (ssadd (entlast) currobj))
(setq coords (list 
(list 960.5625 394.7969) 
(list 1034.585 394.3469) 
(list 1034.585 394.5239) 
(list 960.5625 394.8739)))
(apply 'command (append '("pline") coords '("c")))
(setq currobj (ssadd (entlast) currobj))
(setq coords (list 
(list 960.5625 395.0169) 
(list 1034.585 394.6669) 
(list 1034.585 394.8439) 
(list 960.5625 395.0939)))
(apply 'command (append '("pline") coords '("c")))
(setq currobj (ssadd (entlast) currobj))
(setq coords (list 
(list 960.5625 395.2369) 
(list 1034.585 394.9869) 
(list 1034.585 395.1639) 
(list 960.5625 395.3139)))
(apply 'command (append '("pline") coords '("c")))
(setq currobj (ssadd (entlast) currobj))
(setq coords (list 
(list 960.5625 395.4569) 
(list 1034.585 395.3069) 
(list 1034.585 395.4839) 
(list 960.5625 395.5339)))
(apply 'command (append '("pline") coords '("c")))
(setq currobj (ssadd (entlast) currobj))
(setq coords (list 
(list 960.5625 395.6769) 
(list 1034.585 395.6269) 
(list 1034.585 395.8039) 
(list 960.5625 395.7539)))
(apply 'command (append '("pline") coords '("c")))
(setq currobj (ssadd (entlast) currobj))
(setq coords (list 
(list 960.5625 395.8969) 
(list 1034.585 395.9469) 
(list 1034.585 396.1239) 
(list 960.5625 395.9739)))
(apply 'command (append '("pline") coords '("c")))
(setq currobj (ssadd (entlast) currobj))
(setq coords (list 
(list 960.5625 396.1169) 
(list 1034.585 396.2669) 
(list 1034.585 396.4439) 
(list 960.5625 396.1939)))
(apply 'command (append '("pline") coords '("c")))
(setq currobj (ssadd (entlast) currobj))
(setq coords (list 
(list 960.5625 396.3369) 
(list 1034.585 396.5869) 
(list 1034.585 396.7639) 
(list 960.5625 396.4139)))
(apply 'command (append '("pline") coords '("c")))
(setq currobj (ssadd (entlast) currobj))
(setq coords (list 
(list 960.5625 396.5569) 
(list 1034.585 396.9069) 
(list 1034.585 397.0839) 
(list 960.5625 396.6339)))
(apply 'command (append '("pline") coords '("c")))
(setq currobj (ssadd (entlast) currobj))
(setq coords (list 
(list 960.5625 396.7769) 
(list 1034.585 397.2269) 
(list 1034.585 397.4039) 
(list 960.5625 396.8539)))
(apply 'command (append '("pline") coords '("c")))
(setq currobj (ssadd (entlast) currobj))
(setq coords (list 
(list 960.5625 396.9969) 
(list 1034.585 397.5469) 
(list 1034.585 397.7239) 
(list 960.5625 397.0739)))
(apply 'command (append '("pline") coords '("c")))
(setq currobj (ssadd (entlast) currobj))
(setq coords (list 
(list 960.5625 397.2169) 
(list 1034.585 397.8669) 
(list 1034.585 398.0439) 
(list 960.5625 397.2939)))
(apply 'command (append '("pline") coords '("c")))
(setq currobj (ssadd (entlast) currobj))
(setq coords (list 
(list 959.4375 397.2939) 
(list 885.415 398.0439) 
(list 885.415 397.8669) 
(list 959.4375 397.2169)))
(apply 'command (append '("pline") coords '("c")))
(setq currobj (ssadd (entlast) currobj))
(setq coords (list 
(list 959.4375 397.0739) 
(list 885.415 397.7239) 
(list 885.415 397.5469) 
(list 959.4375 396.9969)))
(apply 'command (append '("pline") coords '("c")))
(setq currobj (ssadd (entlast) currobj))
(setq coords (list 
(list 959.4375 396.8539) 
(list 885.415 397.4039) 
(list 885.415 397.2269) 
(list 959.4375 396.7769)))
(apply 'command (append '("pline") coords '("c")))
(setq currobj (ssadd (entlast) currobj))
(setq coords (list 
(list 959.4375 396.6339) 
(list 885.415 397.0839) 
(list 885.415 396.9069) 
(list 959.4375 396.5569)))
(apply 'command (append '("pline") coords '("c")))
(setq currobj (ssadd (entlast) currobj))
(setq coords (list 
(list 959.4375 396.4139) 
(list 885.415 396.7639) 
(list 885.415 396.5869) 
(list 959.4375 396.3369)))
(apply 'command (append '("pline") coords '("c")))
(setq currobj (ssadd (entlast) currobj))
(setq coords (list 
(list 959.4375 396.1939) 
(list 885.415 396.4439) 
(list 885.415 396.2669) 
(list 959.4375 396.1169)))
(apply 'command (append '("pline") coords '("c")))
(setq currobj (ssadd (entlast) currobj))
(setq coords (list 
(list 959.4375 395.9739) 
(list 885.415 396.1239) 
(list 885.415 395.9469) 
(list 959.4375 395.8969)))
(apply 'command (append '("pline") coords '("c")))
(setq currobj (ssadd (entlast) currobj))
(setq coords (list 
(list 959.4375 395.7539) 
(list 885.415 395.8039) 
(list 885.415 395.6269) 
(list 959.4375 395.6769)))
(apply 'command (append '("pline") coords '("c")))
(setq currobj (ssadd (entlast) currobj))
(setq coords (list 
(list 959.4375 395.5339) 
(list 885.415 395.4839) 
(list 885.415 395.3069) 
(list 959.4375 395.4569)))
(apply 'command (append '("pline") coords '("c")))
(setq currobj (ssadd (entlast) currobj))
(setq coords (list 
(list 959.4375 395.3139) 
(list 885.415 395.1639) 
(list 885.415 394.9869) 
(list 959.4375 395.2369)))
(apply 'command (append '("pline") coords '("c")))
(setq currobj (ssadd (entlast) currobj))
(setq coords (list 
(list 959.4375 395.0939) 
(list 885.415 394.8439) 
(list 885.415 394.6669) 
(list 959.4375 395.0169)))
(apply 'command (append '("pline") coords '("c")))
(setq currobj (ssadd (entlast) currobj))
(setq coords (list 
(list 959.4375 394.8739) 
(list 885.415 394.5239) 
(list 885.415 394.3469) 
(list 959.4375 394.7969)))
(apply 'command (append '("pline") coords '("c")))
(setq currobj (ssadd (entlast) currobj))
(setq coords (list 
(list 959.4375 394.6539) 
(list 885.415 394.2039) 
(list 885.415 394.0269) 
(list 959.4375 394.5769)))
(apply 'command (append '("pline") coords '("c")))
(setq currobj (ssadd (entlast) currobj))
(setq coords (list 
(list 959.4375 394.4339) 
(list 885.415 393.8839) 
(list 885.415 393.7069) 
(list 959.4375 394.3569)))
(apply 'command (append '("pline") coords '("c")))
(setq currobj (ssadd (entlast) currobj))
(setq coords (list 
(list 959.4375 394.2139) 
(list 885.415 393.5639) 
(list 885.415 393.3869) 
(list 959.4375 394.1369)))
(apply 'command (append '("pline") coords '("c")))
(setq currobj (ssadd (entlast) currobj))
(command "_layer" "set" "nitride" "")
(command "_layer" "set" "text" "")
(command "_circle" "959.0625,382.9939" "0.075")
(command "_circle" "959.0625,383.2939" "0.075")
(command "_circle" "959.0625,383.5939" "0.075")
(command "_circle" "959.0625,383.8939" "0.075")
(command "_circle" "959.0625,384.1939" "0.075")
(command "_circle" "958.7625,382.9939" "0.075")
(command "_circle" "958.7625,383.2939" "0.075")
(command "_circle" "958.7625,383.5939" "0.075")
(command "_circle" "958.7625,383.8939" "0.075")
(command "_circle" "958.7625,384.1939" "0.075")
(command "_circle" "958.4625,382.9939" "0.075")
(command "_circle" "958.4625,383.2939" "0.075")
(command "_circle" "958.4625,383.5939" "0.075")
(command "_circle" "958.4625,383.8939" "0.075")
(command "_circle" "958.4625,384.1939" "0.075")
(command "_circle" "958.1625,382.9939" "0.075")
(command "_circle" "958.1625,383.2939" "0.075")
(command "_circle" "958.1625,383.5939" "0.075")
(command "_circle" "958.1625,383.8939" "0.075")
(command "_circle" "958.1625,384.1939" "0.075")
(command "_circle" "957.8625,382.9939" "0.075")
(command "_circle" "957.8625,383.2939" "0.075")
(command "_circle" "957.8625,383.5939" "0.075")
(command "_circle" "957.8625,383.8939" "0.075")
(command "_circle" "957.8625,384.1939" "0.075")
(command "_layer" "set" "nitride" "")
(setq coords (list 
(list 960.2625 408.4369) 
(list 960.2625 524.0816) 
(list 959.7375 524.0816) 
(list 959.7375 408.4369)))
(apply 'command (append '("pline") coords '("c")))
(setq currobj (ssadd (entlast) currobj))
(command "_layer" "set" "prebias" "")
(command "_rectangle" "959.7375,408.4369" "960.2625,524.0816")
(setq currobj (ssadd (entlast) currobj))
(command "_layer" "set" "nitride" "")
(setq coords (list 
(list 960.2625 524.0816) 
(list 960.5625 534.0816) 
(list 960.5625 534.0816) 
(list 960.5625 535.0816) 
(list 1034.585 534.3316) 
(list 1034.585 539.2746) 
(list 960.5625 538.5246) 
(list 960.5625 539.5246) 
(list 960.5625 539.5246) 
(list 960.2625 549.5246) 
(list 959.7375 549.5246) 
(list 959.4375 539.5246) 
(list 959.4375 539.5246) 
(list 959.4375 538.5246) 
(list 885.415 539.2746) 
(list 885.415 534.3316) 
(list 959.4375 535.0816) 
(list 959.4375 534.0816) 
(list 959.4375 534.0816) 
(list 959.7375 524.0816)))
(apply 'command (append '("pline") coords '("c")))
(setq currobj (ssadd (entlast) currobj))
(command "_layer" "set" "prebias" "")
(setq coords (list 
(list 959.4375 524.0816) 
(list 959.4375 535.0816) 
(list 885.415 534.3316) 
(list 885.415 539.2746) 
(list 959.4375 538.5246) 
(list 959.4375 549.5246) 
(list 960.5625 549.5246) 
(list 960.5625 538.5246) 
(list 1034.585 539.2746) 
(list 1034.585 534.3316) 
(list 960.5625 535.0816) 
(list 960.5625 524.0816)))
(apply 'command (append '("pline") coords '("c")))
(setq currobj (ssadd (entlast) currobj))
(command "_layer" "set" "nitride" "")
(command "_layer" "set" "fda1" "")
(setq coords (list 
(list 960.5625 535.2246) 
(list 1034.585 534.4746) 
(list 1034.585 534.6516) 
(list 960.5625 535.3016)))
(apply 'command (append '("pline") coords '("c")))
(setq currobj (ssadd (entlast) currobj))
(setq coords (list 
(list 960.5625 535.4446) 
(list 1034.585 534.7946) 
(list 1034.585 534.9716) 
(list 960.5625 535.5216)))
(apply 'command (append '("pline") coords '("c")))
(setq currobj (ssadd (entlast) currobj))
(setq coords (list 
(list 960.5625 535.6646) 
(list 1034.585 535.1146) 
(list 1034.585 535.2916) 
(list 960.5625 535.7416)))
(apply 'command (append '("pline") coords '("c")))
(setq currobj (ssadd (entlast) currobj))
(setq coords (list 
(list 960.5625 535.8846) 
(list 1034.585 535.4346) 
(list 1034.585 535.6116) 
(list 960.5625 535.9616)))
(apply 'command (append '("pline") coords '("c")))
(setq currobj (ssadd (entlast) currobj))
(setq coords (list 
(list 960.5625 536.1046) 
(list 1034.585 535.7546) 
(list 1034.585 535.9316) 
(list 960.5625 536.1816)))
(apply 'command (append '("pline") coords '("c")))
(setq currobj (ssadd (entlast) currobj))
(setq coords (list 
(list 960.5625 536.3246) 
(list 1034.585 536.0746) 
(list 1034.585 536.2516) 
(list 960.5625 536.4016)))
(apply 'command (append '("pline") coords '("c")))
(setq currobj (ssadd (entlast) currobj))
(setq coords (list 
(list 960.5625 536.5446) 
(list 1034.585 536.3946) 
(list 1034.585 536.5716) 
(list 960.5625 536.6216)))
(apply 'command (append '("pline") coords '("c")))
(setq currobj (ssadd (entlast) currobj))
(setq coords (list 
(list 960.5625 536.7646) 
(list 1034.585 536.7146) 
(list 1034.585 536.8916) 
(list 960.5625 536.8416)))
(apply 'command (append '("pline") coords '("c")))
(setq currobj (ssadd (entlast) currobj))
(setq coords (list 
(list 960.5625 536.9846) 
(list 1034.585 537.0346) 
(list 1034.585 537.2116) 
(list 960.5625 537.0616)))
(apply 'command (append '("pline") coords '("c")))
(setq currobj (ssadd (entlast) currobj))
(setq coords (list 
(list 960.5625 537.2046) 
(list 1034.585 537.3546) 
(list 1034.585 537.5316) 
(list 960.5625 537.2816)))
(apply 'command (append '("pline") coords '("c")))
(setq currobj (ssadd (entlast) currobj))
(setq coords (list 
(list 960.5625 537.4246) 
(list 1034.585 537.6746) 
(list 1034.585 537.8516) 
(list 960.5625 537.5016)))
(apply 'command (append '("pline") coords '("c")))
(setq currobj (ssadd (entlast) currobj))
(setq coords (list 
(list 960.5625 537.6446) 
(list 1034.585 537.9946) 
(list 1034.585 538.1716) 
(list 960.5625 537.7216)))
(apply 'command (append '("pline") coords '("c")))
(setq currobj (ssadd (entlast) currobj))
(setq coords (list 
(list 960.5625 537.8646) 
(list 1034.585 538.3146) 
(list 1034.585 538.4916) 
(list 960.5625 537.9416)))
(apply 'command (append '("pline") coords '("c")))
(setq currobj (ssadd (entlast) currobj))
(setq coords (list 
(list 960.5625 538.0846) 
(list 1034.585 538.6346) 
(list 1034.585 538.8116) 
(list 960.5625 538.1616)))
(apply 'command (append '("pline") coords '("c")))
(setq currobj (ssadd (entlast) currobj))
(setq coords (list 
(list 960.5625 538.3046) 
(list 1034.585 538.9546) 
(list 1034.585 539.1316) 
(list 960.5625 538.3816)))
(apply 'command (append '("pline") coords '("c")))
(setq currobj (ssadd (entlast) currobj))
(setq coords (list 
(list 959.4375 538.3816) 
(list 885.415 539.1316) 
(list 885.415 538.9546) 
(list 959.4375 538.3046)))
(apply 'command (append '("pline") coords '("c")))
(setq currobj (ssadd (entlast) currobj))
(setq coords (list 
(list 959.4375 538.1616) 
(list 885.415 538.8116) 
(list 885.415 538.6346) 
(list 959.4375 538.0846)))
(apply 'command (append '("pline") coords '("c")))
(setq currobj (ssadd (entlast) currobj))
(setq coords (list 
(list 959.4375 537.9416) 
(list 885.415 538.4916) 
(list 885.415 538.3146) 
(list 959.4375 537.8646)))
(apply 'command (append '("pline") coords '("c")))
(setq currobj (ssadd (entlast) currobj))
(setq coords (list 
(list 959.4375 537.7216) 
(list 885.415 538.1716) 
(list 885.415 537.9946) 
(list 959.4375 537.6446)))
(apply 'command (append '("pline") coords '("c")))
(setq currobj (ssadd (entlast) currobj))
(setq coords (list 
(list 959.4375 537.5016) 
(list 885.415 537.8516) 
(list 885.415 537.6746) 
(list 959.4375 537.4246)))
(apply 'command (append '("pline") coords '("c")))
(setq currobj (ssadd (entlast) currobj))
(setq coords (list 
(list 959.4375 537.2816) 
(list 885.415 537.5316) 
(list 885.415 537.3546) 
(list 959.4375 537.2046)))
(apply 'command (append '("pline") coords '("c")))
(setq currobj (ssadd (entlast) currobj))
(setq coords (list 
(list 959.4375 537.0616) 
(list 885.415 537.2116) 
(list 885.415 537.0346) 
(list 959.4375 536.9846)))
(apply 'command (append '("pline") coords '("c")))
(setq currobj (ssadd (entlast) currobj))
(setq coords (list 
(list 959.4375 536.8416) 
(list 885.415 536.8916) 
(list 885.415 536.7146) 
(list 959.4375 536.7646)))
(apply 'command (append '("pline") coords '("c")))
(setq currobj (ssadd (entlast) currobj))
(setq coords (list 
(list 959.4375 536.6216) 
(list 885.415 536.5716) 
(list 885.415 536.3946) 
(list 959.4375 536.5446)))
(apply 'command (append '("pline") coords '("c")))
(setq currobj (ssadd (entlast) currobj))
(setq coords (list 
(list 959.4375 536.4016) 
(list 885.415 536.2516) 
(list 885.415 536.0746) 
(list 959.4375 536.3246)))
(apply 'command (append '("pline") coords '("c")))
(setq currobj (ssadd (entlast) currobj))
(setq coords (list 
(list 959.4375 536.1816) 
(list 885.415 535.9316) 
(list 885.415 535.7546) 
(list 959.4375 536.1046)))
(apply 'command (append '("pline") coords '("c")))
(setq currobj (ssadd (entlast) currobj))
(setq coords (list 
(list 959.4375 535.9616) 
(list 885.415 535.6116) 
(list 885.415 535.4346) 
(list 959.4375 535.8846)))
(apply 'command (append '("pline") coords '("c")))
(setq currobj (ssadd (entlast) currobj))
(setq coords (list 
(list 959.4375 535.7416) 
(list 885.415 535.2916) 
(list 885.415 535.1146) 
(list 959.4375 535.6646)))
(apply 'command (append '("pline") coords '("c")))
(setq currobj (ssadd (entlast) currobj))
(setq coords (list 
(list 959.4375 535.5216) 
(list 885.415 534.9716) 
(list 885.415 534.7946) 
(list 959.4375 535.4446)))
(apply 'command (append '("pline") coords '("c")))
(setq currobj (ssadd (entlast) currobj))
(setq coords (list 
(list 959.4375 535.3016) 
(list 885.415 534.6516) 
(list 885.415 534.4746) 
(list 959.4375 535.2246)))
(apply 'command (append '("pline") coords '("c")))
(setq currobj (ssadd (entlast) currobj))
(command "_layer" "set" "nitride" "")
(command "_layer" "set" "text" "")
(command "_circle" "959.0625,524.0816" "0.075")
(command "_circle" "959.0625,524.3816" "0.075")
(command "_circle" "959.0625,524.6816" "0.075")
(command "_circle" "959.0625,524.9816" "0.075")
(command "_circle" "959.0625,525.2816" "0.075")
(command "_circle" "958.7625,524.0816" "0.075")
(command "_circle" "958.7625,524.3816" "0.075")
(command "_circle" "958.7625,524.6816" "0.075")
(command "_circle" "958.7625,524.9816" "0.075")
(command "_circle" "958.7625,525.2816" "0.075")
(command "_circle" "958.4625,524.0816" "0.075")
(command "_circle" "958.4625,524.3816" "0.075")
(command "_circle" "958.4625,524.6816" "0.075")
(command "_circle" "958.4625,524.9816" "0.075")
(command "_circle" "958.4625,525.2816" "0.075")
(command "_circle" "958.1625,524.0816" "0.075")
(command "_circle" "958.1625,524.3816" "0.075")
(command "_circle" "958.1625,524.6816" "0.075")
(command "_circle" "958.1625,524.9816" "0.075")
(command "_circle" "958.1625,525.2816" "0.075")
(command "_circle" "957.8625,524.0816" "0.075")
(command "_circle" "957.8625,524.3816" "0.075")
(command "_circle" "957.8625,524.6816" "0.075")
(command "_circle" "957.8625,524.9816" "0.075")
(command "_circle" "957.8625,525.2816" "0.075")
(command "_layer" "set" "nitride" "")
(setq coords (list 
(list 960.2625 549.5246) 
(list 960.2625 665.1693) 
(list 959.7375 665.1693) 
(list 959.7375 549.5246)))
(apply 'command (append '("pline") coords '("c")))
(setq currobj (ssadd (entlast) currobj))
(command "_layer" "set" "prebias" "")
(command "_rectangle" "959.7375,549.5246" "960.2625,665.1693")
(setq currobj (ssadd (entlast) currobj))
(command "_layer" "set" "nitride" "")
(setq coords (list 
(list 960.2625 665.1693) 
(list 960.5625 675.1693) 
(list 960.5625 675.1693) 
(list 960.5625 676.1693) 
(list 1034.585 675.4193) 
(list 1034.585 680.3623) 
(list 960.5625 679.6123) 
(list 960.5625 680.6123) 
(list 960.5625 680.6123) 
(list 960.2625 690.6123) 
(list 959.7375 690.6123) 
(list 959.4375 680.6123) 
(list 959.4375 680.6123) 
(list 959.4375 679.6123) 
(list 885.415 680.3623) 
(list 885.415 675.4193) 
(list 959.4375 676.1693) 
(list 959.4375 675.1693) 
(list 959.4375 675.1693) 
(list 959.7375 665.1693)))
(apply 'command (append '("pline") coords '("c")))
(setq currobj (ssadd (entlast) currobj))
(command "_layer" "set" "prebias" "")
(setq coords (list 
(list 959.4375 665.1693) 
(list 959.4375 676.1693) 
(list 885.415 675.4193) 
(list 885.415 680.3623) 
(list 959.4375 679.6123) 
(list 959.4375 690.6123) 
(list 960.5625 690.6123) 
(list 960.5625 679.6123) 
(list 1034.585 680.3623) 
(list 1034.585 675.4193) 
(list 960.5625 676.1693) 
(list 960.5625 665.1693)))
(apply 'command (append '("pline") coords '("c")))
(setq currobj (ssadd (entlast) currobj))
(command "_layer" "set" "nitride" "")
(command "_layer" "set" "fda1" "")
(setq coords (list 
(list 960.5625 676.3123) 
(list 1034.585 675.5623) 
(list 1034.585 675.7393) 
(list 960.5625 676.3893)))
(apply 'command (append '("pline") coords '("c")))
(setq currobj (ssadd (entlast) currobj))
(setq coords (list 
(list 960.5625 676.5323) 
(list 1034.585 675.8823) 
(list 1034.585 676.0593) 
(list 960.5625 676.6093)))
(apply 'command (append '("pline") coords '("c")))
(setq currobj (ssadd (entlast) currobj))
(setq coords (list 
(list 960.5625 676.7523) 
(list 1034.585 676.2023) 
(list 1034.585 676.3793) 
(list 960.5625 676.8293)))
(apply 'command (append '("pline") coords '("c")))
(setq currobj (ssadd (entlast) currobj))
(setq coords (list 
(list 960.5625 676.9723) 
(list 1034.585 676.5223) 
(list 1034.585 676.6993) 
(list 960.5625 677.0493)))
(apply 'command (append '("pline") coords '("c")))
(setq currobj (ssadd (entlast) currobj))
(setq coords (list 
(list 960.5625 677.1923) 
(list 1034.585 676.8423) 
(list 1034.585 677.0193) 
(list 960.5625 677.2693)))
(apply 'command (append '("pline") coords '("c")))
(setq currobj (ssadd (entlast) currobj))
(setq coords (list 
(list 960.5625 677.4123) 
(list 1034.585 677.1623) 
(list 1034.585 677.3393) 
(list 960.5625 677.4893)))
(apply 'command (append '("pline") coords '("c")))
(setq currobj (ssadd (entlast) currobj))
(setq coords (list 
(list 960.5625 677.6323) 
(list 1034.585 677.4823) 
(list 1034.585 677.6593) 
(list 960.5625 677.7093)))
(apply 'command (append '("pline") coords '("c")))
(setq currobj (ssadd (entlast) currobj))
(setq coords (list 
(list 960.5625 677.8523) 
(list 1034.585 677.8023) 
(list 1034.585 677.9793) 
(list 960.5625 677.9293)))
(apply 'command (append '("pline") coords '("c")))
(setq currobj (ssadd (entlast) currobj))
(setq coords (list 
(list 960.5625 678.0723) 
(list 1034.585 678.1223) 
(list 1034.585 678.2993) 
(list 960.5625 678.1493)))
(apply 'command (append '("pline") coords '("c")))
(setq currobj (ssadd (entlast) currobj))
(setq coords (list 
(list 960.5625 678.2923) 
(list 1034.585 678.4423) 
(list 1034.585 678.6193) 
(list 960.5625 678.3693)))
(apply 'command (append '("pline") coords '("c")))
(setq currobj (ssadd (entlast) currobj))
(setq coords (list 
(list 960.5625 678.5123) 
(list 1034.585 678.7623) 
(list 1034.585 678.9393) 
(list 960.5625 678.5893)))
(apply 'command (append '("pline") coords '("c")))
(setq currobj (ssadd (entlast) currobj))
(setq coords (list 
(list 960.5625 678.7323) 
(list 1034.585 679.0823) 
(list 1034.585 679.2593) 
(list 960.5625 678.8093)))
(apply 'command (append '("pline") coords '("c")))
(setq currobj (ssadd (entlast) currobj))
(setq coords (list 
(list 960.5625 678.9523) 
(list 1034.585 679.4023) 
(list 1034.585 679.5793) 
(list 960.5625 679.0293)))
(apply 'command (append '("pline") coords '("c")))
(setq currobj (ssadd (entlast) currobj))
(setq coords (list 
(list 960.5625 679.1723) 
(list 1034.585 679.7223) 
(list 1034.585 679.8993) 
(list 960.5625 679.2493)))
(apply 'command (append '("pline") coords '("c")))
(setq currobj (ssadd (entlast) currobj))
(setq coords (list 
(list 960.5625 679.3923) 
(list 1034.585 680.0423) 
(list 1034.585 680.2193) 
(list 960.5625 679.4693)))
(apply 'command (append '("pline") coords '("c")))
(setq currobj (ssadd (entlast) currobj))
(setq coords (list 
(list 959.4375 679.4693) 
(list 885.415 680.2193) 
(list 885.415 680.0423) 
(list 959.4375 679.3923)))
(apply 'command (append '("pline") coords '("c")))
(setq currobj (ssadd (entlast) currobj))
(setq coords (list 
(list 959.4375 679.2493) 
(list 885.415 679.8993) 
(list 885.415 679.7223) 
(list 959.4375 679.1723)))
(apply 'command (append '("pline") coords '("c")))
(setq currobj (ssadd (entlast) currobj))
(setq coords (list 
(list 959.4375 679.0293) 
(list 885.415 679.5793) 
(list 885.415 679.4023) 
(list 959.4375 678.9523)))
(apply 'command (append '("pline") coords '("c")))
(setq currobj (ssadd (entlast) currobj))
(setq coords (list 
(list 959.4375 678.8093) 
(list 885.415 679.2593) 
(list 885.415 679.0823) 
(list 959.4375 678.7323)))
(apply 'command (append '("pline") coords '("c")))
(setq currobj (ssadd (entlast) currobj))
(setq coords (list 
(list 959.4375 678.5893) 
(list 885.415 678.9393) 
(list 885.415 678.7623) 
(list 959.4375 678.5123)))
(apply 'command (append '("pline") coords '("c")))
(setq currobj (ssadd (entlast) currobj))
(setq coords (list 
(list 959.4375 678.3693) 
(list 885.415 678.6193) 
(list 885.415 678.4423) 
(list 959.4375 678.2923)))
(apply 'command (append '("pline") coords '("c")))
(setq currobj (ssadd (entlast) currobj))
(setq coords (list 
(list 959.4375 678.1493) 
(list 885.415 678.2993) 
(list 885.415 678.1223) 
(list 959.4375 678.0723)))
(apply 'command (append '("pline") coords '("c")))
(setq currobj (ssadd (entlast) currobj))
(setq coords (list 
(list 959.4375 677.9293) 
(list 885.415 677.9793) 
(list 885.415 677.8023) 
(list 959.4375 677.8523)))
(apply 'command (append '("pline") coords '("c")))
(setq currobj (ssadd (entlast) currobj))
(setq coords (list 
(list 959.4375 677.7093) 
(list 885.415 677.6593) 
(list 885.415 677.4823) 
(list 959.4375 677.6323)))
(apply 'command (append '("pline") coords '("c")))
(setq currobj (ssadd (entlast) currobj))
(setq coords (list 
(list 959.4375 677.4893) 
(list 885.415 677.3393) 
(list 885.415 677.1623) 
(list 959.4375 677.4123)))
(apply 'command (append '("pline") coords '("c")))
(setq currobj (ssadd (entlast) currobj))
(setq coords (list 
(list 959.4375 677.2693) 
(list 885.415 677.0193) 
(list 885.415 676.8423) 
(list 959.4375 677.1923)))
(apply 'command (append '("pline") coords '("c")))
(setq currobj (ssadd (entlast) currobj))
(setq coords (list 
(list 959.4375 677.0493) 
(list 885.415 676.6993) 
(list 885.415 676.5223) 
(list 959.4375 676.9723)))
(apply 'command (append '("pline") coords '("c")))
(setq currobj (ssadd (entlast) currobj))
(setq coords (list 
(list 959.4375 676.8293) 
(list 885.415 676.3793) 
(list 885.415 676.2023) 
(list 959.4375 676.7523)))
(apply 'command (append '("pline") coords '("c")))
(setq currobj (ssadd (entlast) currobj))
(setq coords (list 
(list 959.4375 676.6093) 
(list 885.415 676.0593) 
(list 885.415 675.8823) 
(list 959.4375 676.5323)))
(apply 'command (append '("pline") coords '("c")))
(setq currobj (ssadd (entlast) currobj))
(setq coords (list 
(list 959.4375 676.3893) 
(list 885.415 675.7393) 
(list 885.415 675.5623) 
(list 959.4375 676.3123)))
(apply 'command (append '("pline") coords '("c")))
(setq currobj (ssadd (entlast) currobj))
(command "_layer" "set" "nitride" "")
(command "_layer" "set" "text" "")
(command "_circle" "959.0625,665.1693" "0.075")
(command "_circle" "959.0625,665.4693" "0.075")
(command "_circle" "959.0625,665.7693" "0.075")
(command "_circle" "959.0625,666.0693" "0.075")
(command "_circle" "959.0625,666.3693" "0.075")
(command "_circle" "958.7625,665.1693" "0.075")
(command "_circle" "958.7625,665.4693" "0.075")
(command "_circle" "958.7625,665.7693" "0.075")
(command "_circle" "958.7625,666.0693" "0.075")
(command "_circle" "958.7625,666.3693" "0.075")
(command "_circle" "958.4625,665.1693" "0.075")
(command "_circle" "958.4625,665.4693" "0.075")
(command "_circle" "958.4625,665.7693" "0.075")
(command "_circle" "958.4625,666.0693" "0.075")
(command "_circle" "958.4625,666.3693" "0.075")
(command "_circle" "958.1625,665.1693" "0.075")
(command "_circle" "958.1625,665.4693" "0.075")
(command "_circle" "958.1625,665.7693" "0.075")
(command "_circle" "958.1625,666.0693" "0.075")
(command "_circle" "958.1625,666.3693" "0.075")
(command "_circle" "957.8625,665.1693" "0.075")
(command "_circle" "957.8625,665.4693" "0.075")
(command "_circle" "957.8625,665.7693" "0.075")
(command "_circle" "957.8625,666.0693" "0.075")
(command "_circle" "957.8625,666.3693" "0.075")
(command "_layer" "set" "nitride" "")
(setq coords (list 
(list 960.2625 690.6123) 
(list 960.2625 806.257) 
(list 959.7375 806.257) 
(list 959.7375 690.6123)))
(apply 'command (append '("pline") coords '("c")))
(setq currobj (ssadd (entlast) currobj))
(command "_layer" "set" "prebias" "")
(command "_rectangle" "959.7375,690.6123" "960.2625,806.257")
(setq currobj (ssadd (entlast) currobj))
(command "_layer" "set" "nitride" "")
(setq coords (list 
(list 960.2625 806.257) 
(list 960.5625 816.257) 
(list 960.5625 816.257) 
(list 960.5625 817.257) 
(list 1034.585 816.507) 
(list 1034.585 821.45) 
(list 960.5625 820.7) 
(list 960.5625 821.7) 
(list 960.5625 821.7) 
(list 960.2625 831.7) 
(list 959.7375 831.7) 
(list 959.4375 821.7) 
(list 959.4375 821.7) 
(list 959.4375 820.7) 
(list 885.415 821.45) 
(list 885.415 816.507) 
(list 959.4375 817.257) 
(list 959.4375 816.257) 
(list 959.4375 816.257) 
(list 959.7375 806.257)))
(apply 'command (append '("pline") coords '("c")))
(setq currobj (ssadd (entlast) currobj))
(command "_layer" "set" "prebias" "")
(setq coords (list 
(list 959.4375 806.257) 
(list 959.4375 817.257) 
(list 885.415 816.507) 
(list 885.415 821.45) 
(list 959.4375 820.7) 
(list 959.4375 831.7) 
(list 960.5625 831.7) 
(list 960.5625 820.7) 
(list 1034.585 821.45) 
(list 1034.585 816.507) 
(list 960.5625 817.257) 
(list 960.5625 806.257)))
(apply 'command (append '("pline") coords '("c")))
(setq currobj (ssadd (entlast) currobj))
(command "_layer" "set" "nitride" "")
(command "_layer" "set" "fda1" "")
(setq coords (list 
(list 960.5625 817.4) 
(list 1034.585 816.65) 
(list 1034.585 816.827) 
(list 960.5625 817.477)))
(apply 'command (append '("pline") coords '("c")))
(setq currobj (ssadd (entlast) currobj))
(setq coords (list 
(list 960.5625 817.62) 
(list 1034.585 816.97) 
(list 1034.585 817.147) 
(list 960.5625 817.697)))
(apply 'command (append '("pline") coords '("c")))
(setq currobj (ssadd (entlast) currobj))
(setq coords (list 
(list 960.5625 817.84) 
(list 1034.585 817.29) 
(list 1034.585 817.467) 
(list 960.5625 817.917)))
(apply 'command (append '("pline") coords '("c")))
(setq currobj (ssadd (entlast) currobj))
(setq coords (list 
(list 960.5625 818.06) 
(list 1034.585 817.61) 
(list 1034.585 817.787) 
(list 960.5625 818.137)))
(apply 'command (append '("pline") coords '("c")))
(setq currobj (ssadd (entlast) currobj))
(setq coords (list 
(list 960.5625 818.28) 
(list 1034.585 817.93) 
(list 1034.585 818.107) 
(list 960.5625 818.357)))
(apply 'command (append '("pline") coords '("c")))
(setq currobj (ssadd (entlast) currobj))
(setq coords (list 
(list 960.5625 818.5) 
(list 1034.585 818.25) 
(list 1034.585 818.427) 
(list 960.5625 818.577)))
(apply 'command (append '("pline") coords '("c")))
(setq currobj (ssadd (entlast) currobj))
(setq coords (list 
(list 960.5625 818.72) 
(list 1034.585 818.57) 
(list 1034.585 818.747) 
(list 960.5625 818.797)))
(apply 'command (append '("pline") coords '("c")))
(setq currobj (ssadd (entlast) currobj))
(setq coords (list 
(list 960.5625 818.94) 
(list 1034.585 818.89) 
(list 1034.585 819.067) 
(list 960.5625 819.017)))
(apply 'command (append '("pline") coords '("c")))
(setq currobj (ssadd (entlast) currobj))
(setq coords (list 
(list 960.5625 819.16) 
(list 1034.585 819.21) 
(list 1034.585 819.387) 
(list 960.5625 819.237)))
(apply 'command (append '("pline") coords '("c")))
(setq currobj (ssadd (entlast) currobj))
(setq coords (list 
(list 960.5625 819.38) 
(list 1034.585 819.53) 
(list 1034.585 819.707) 
(list 960.5625 819.457)))
(apply 'command (append '("pline") coords '("c")))
(setq currobj (ssadd (entlast) currobj))
(setq coords (list 
(list 960.5625 819.6) 
(list 1034.585 819.85) 
(list 1034.585 820.027) 
(list 960.5625 819.677)))
(apply 'command (append '("pline") coords '("c")))
(setq currobj (ssadd (entlast) currobj))
(setq coords (list 
(list 960.5625 819.82) 
(list 1034.585 820.17) 
(list 1034.585 820.347) 
(list 960.5625 819.897)))
(apply 'command (append '("pline") coords '("c")))
(setq currobj (ssadd (entlast) currobj))
(setq coords (list 
(list 960.5625 820.04) 
(list 1034.585 820.49) 
(list 1034.585 820.667) 
(list 960.5625 820.117)))
(apply 'command (append '("pline") coords '("c")))
(setq currobj (ssadd (entlast) currobj))
(setq coords (list 
(list 960.5625 820.26) 
(list 1034.585 820.81) 
(list 1034.585 820.987) 
(list 960.5625 820.337)))
(apply 'command (append '("pline") coords '("c")))
(setq currobj (ssadd (entlast) currobj))
(setq coords (list 
(list 960.5625 820.48) 
(list 1034.585 821.13) 
(list 1034.585 821.307) 
(list 960.5625 820.557)))
(apply 'command (append '("pline") coords '("c")))
(setq currobj (ssadd (entlast) currobj))
(setq coords (list 
(list 959.4375 820.557) 
(list 885.415 821.307) 
(list 885.415 821.13) 
(list 959.4375 820.48)))
(apply 'command (append '("pline") coords '("c")))
(setq currobj (ssadd (entlast) currobj))
(setq coords (list 
(list 959.4375 820.337) 
(list 885.415 820.987) 
(list 885.415 820.81) 
(list 959.4375 820.26)))
(apply 'command (append '("pline") coords '("c")))
(setq currobj (ssadd (entlast) currobj))
(setq coords (list 
(list 959.4375 820.117) 
(list 885.415 820.667) 
(list 885.415 820.49) 
(list 959.4375 820.04)))
(apply 'command (append '("pline") coords '("c")))
(setq currobj (ssadd (entlast) currobj))
(setq coords (list 
(list 959.4375 819.897) 
(list 885.415 820.347) 
(list 885.415 820.17) 
(list 959.4375 819.82)))
(apply 'command (append '("pline") coords '("c")))
(setq currobj (ssadd (entlast) currobj))
(setq coords (list 
(list 959.4375 819.677) 
(list 885.415 820.027) 
(list 885.415 819.85) 
(list 959.4375 819.6)))
(apply 'command (append '("pline") coords '("c")))
(setq currobj (ssadd (entlast) currobj))
(setq coords (list 
(list 959.4375 819.457) 
(list 885.415 819.707) 
(list 885.415 819.53) 
(list 959.4375 819.38)))
(apply 'command (append '("pline") coords '("c")))
(setq currobj (ssadd (entlast) currobj))
(setq coords (list 
(list 959.4375 819.237) 
(list 885.415 819.387) 
(list 885.415 819.21) 
(list 959.4375 819.16)))
(apply 'command (append '("pline") coords '("c")))
(setq currobj (ssadd (entlast) currobj))
(setq coords (list 
(list 959.4375 819.017) 
(list 885.415 819.067) 
(list 885.415 818.89) 
(list 959.4375 818.94)))
(apply 'command (append '("pline") coords '("c")))
(setq currobj (ssadd (entlast) currobj))
(setq coords (list 
(list 959.4375 818.797) 
(list 885.415 818.747) 
(list 885.415 818.57) 
(list 959.4375 818.72)))
(apply 'command (append '("pline") coords '("c")))
(setq currobj (ssadd (entlast) currobj))
(setq coords (list 
(list 959.4375 818.577) 
(list 885.415 818.427) 
(list 885.415 818.25) 
(list 959.4375 818.5)))
(apply 'command (append '("pline") coords '("c")))
(setq currobj (ssadd (entlast) currobj))
(setq coords (list 
(list 959.4375 818.357) 
(list 885.415 818.107) 
(list 885.415 817.93) 
(list 959.4375 818.28)))
(apply 'command (append '("pline") coords '("c")))
(setq currobj (ssadd (entlast) currobj))
(setq coords (list 
(list 959.4375 818.137) 
(list 885.415 817.787) 
(list 885.415 817.61) 
(list 959.4375 818.06)))
(apply 'command (append '("pline") coords '("c")))
(setq currobj (ssadd (entlast) currobj))
(setq coords (list 
(list 959.4375 817.917) 
(list 885.415 817.467) 
(list 885.415 817.29) 
(list 959.4375 817.84)))
(apply 'command (append '("pline") coords '("c")))
(setq currobj (ssadd (entlast) currobj))
(setq coords (list 
(list 959.4375 817.697) 
(list 885.415 817.147) 
(list 885.415 816.97) 
(list 959.4375 817.62)))
(apply 'command (append '("pline") coords '("c")))
(setq currobj (ssadd (entlast) currobj))
(setq coords (list 
(list 959.4375 817.477) 
(list 885.415 816.827) 
(list 885.415 816.65) 
(list 959.4375 817.4)))
(apply 'command (append '("pline") coords '("c")))
(setq currobj (ssadd (entlast) currobj))
(command "_layer" "set" "nitride" "")
(command "_layer" "set" "text" "")
(command "_circle" "959.0625,806.257" "0.075")
(command "_circle" "959.0625,806.557" "0.075")
(command "_circle" "959.0625,806.857" "0.075")
(command "_circle" "959.0625,807.157" "0.075")
(command "_circle" "959.0625,807.457" "0.075")
(command "_circle" "958.7625,806.257" "0.075")
(command "_circle" "958.7625,806.557" "0.075")
(command "_circle" "958.7625,806.857" "0.075")
(command "_circle" "958.7625,807.157" "0.075")
(command "_circle" "958.7625,807.457" "0.075")
(command "_circle" "958.4625,806.257" "0.075")
(command "_circle" "958.4625,806.557" "0.075")
(command "_circle" "958.4625,806.857" "0.075")
(command "_circle" "958.4625,807.157" "0.075")
(command "_circle" "958.4625,807.457" "0.075")
(command "_circle" "958.1625,806.257" "0.075")
(command "_circle" "958.1625,806.557" "0.075")
(command "_circle" "958.1625,806.857" "0.075")
(command "_circle" "958.1625,807.157" "0.075")
(command "_circle" "958.1625,807.457" "0.075")
(command "_circle" "957.8625,806.257" "0.075")
(command "_circle" "957.8625,806.557" "0.075")
(command "_circle" "957.8625,806.857" "0.075")
(command "_circle" "957.8625,807.157" "0.075")
(command "_circle" "957.8625,807.457" "0.075")
(command "_layer" "set" "nitride" "")
(setq coords (list 
(list 960.2625 831.7) 
(list 960.2625 836.7) 
(list 959.7375 836.7) 
(list 959.7375 831.7)))
(apply 'command (append '("pline") coords '("c")))
(setq currobj (ssadd (entlast) currobj))
(command "_layer" "set" "prebias" "")
(command "_rectangle" "959.7375,831.7" "960.2625,836.7")
(setq currobj (ssadd (entlast) currobj))
(command "_layer" "set" "nitride" "")
(setq cooledsinglenanobeam3 currobj)
(setq currobj nil)
(setq currobj (ssadd))
; DRAWING PHOTONIC CRYSTAL
(command "_layer" "set" "negYjunc" "")
(setq coords (list 
(list 960.135 866.7) 
(list 960 851.7) 
(list 960 866.7)))
(apply 'command (append '("pline") coords '("c")))
(setq currobj (ssadd (entlast) currobj))
(setq coords (list 
(list 960.2625 836.7) 
(list 960.415 866.7) 
(list 961.086 866.7) 
(list 961.086 836.7)))
(apply 'command (append '("pline") coords '("c")))
(setq currobj (ssadd (entlast) currobj))
(setq coords (list 
(list 959.865 866.7) 
(list 960 851.7) 
(list 960 866.7)))
(apply 'command (append '("pline") coords '("c")))
(setq currobj (ssadd (entlast) currobj))
(setq coords (list 
(list 959.7375 836.7) 
(list 959.585 866.7) 
(list 958.914 866.7) 
(list 958.914 836.7)))
(apply 'command (append '("pline") coords '("c")))
(setq currobj (ssadd (entlast) currobj))
(command "_layer" "set" "nitride" "")
(setq yjunction3 currobj)
(setq currobj nil)
(setq currobj (ssadd))
(setq tap3 nil)
(setq tap3 (ssadd))
(command "_layer" "set" "phc" "")
(setq coords (list 
(list 960 866.7) 
(list 960.135 866.7) 
(list 960.135 866.7103) 
(list 960.135 866.7206) 
(list 960.135 866.7308) 
(list 960.135 866.7411) 
(list 960.135 866.7514) 
(list 960.135 866.7617) 
(list 960.135 866.7719) 
(list 960.135 866.7822) 
(list 960.135 866.7925) 
(list 960.135 866.8028) 
(list 960.135 866.8131) 
(list 960.135 866.8233) 
(list 960.135 866.8336) 
(list 960.135 866.8439) 
(list 960.135 866.8542) 
(list 960.135 866.8644) 
(list 960.135 866.8747) 
(list 960.135 866.885) 
(list 960.135 866.8953) 
(list 960.135 866.9056) 
(list 960.135 866.9158) 
(list 960.135 866.9261) 
(list 960.135 866.9364) 
(list 960.135 866.9467) 
(list 960.135 866.9569) 
(list 960.135 866.9672) 
(list 960.135 866.9775) 
(list 960.135 866.9878) 
(list 960.135 866.9981) 
(list 960.135 867.0083) 
(list 960.135 867.0186) 
(list 960.135 867.0289) 
(list 960.135 867.0392) 
(list 960.135 867.0494) 
(list 960.135 867.0597) 
(list 960.135 867.07) 
(list 960 867.07)))
(apply 'command (append '("pline") coords '("c")))
(setq tap3 (ssadd (entlast) tap3))
(command "_mirror" (entlast) "" "960,900" "960,901" "No")
(setq tap3 (ssadd (entlast) tap3))
(setq coords (list 
(list 960.4235 866.7) 
(list 960.415 866.7) 
(list 960.4152 866.7103) 
(list 960.4154 866.7206) 
(list 960.4156 866.7308) 
(list 960.4157 866.7411) 
(list 960.4157 866.7514) 
(list 960.4157 866.7617) 
(list 960.4155 866.7719) 
(list 960.4153 866.7822) 
(list 960.4149 866.7925) 
(list 960.4145 866.8028) 
(list 960.414 866.8131) 
(list 960.4134 866.8233) 
(list 960.4129 866.8336) 
(list 960.4123 866.8439) 
(list 960.4117 866.8542) 
(list 960.4112 866.8644) 
(list 960.4108 866.8747) 
(list 960.4105 866.885) 
(list 960.4103 866.8953) 
(list 960.4103 866.9056) 
(list 960.4104 866.9158) 
(list 960.4107 866.9261) 
(list 960.4112 866.9364) 
(list 960.4119 866.9467) 
(list 960.4127 866.9569) 
(list 960.4137 866.9672) 
(list 960.4148 866.9775) 
(list 960.416 866.9878) 
(list 960.4172 866.9981) 
(list 960.4184 867.0083) 
(list 960.4196 867.0186) 
(list 960.4208 867.0289) 
(list 960.4217 867.0392) 
(list 960.4226 867.0494) 
(list 960.4232 867.0597) 
(list 960.4235 867.07) 
(list 960.4235 867.07)))
(apply 'command (append '("pline") coords '("c")))
(setq tap3 (ssadd (entlast) tap3))
(command "_mirror" (entlast) "" "960,900" "960,901" "No")
(setq tap3 (ssadd (entlast) tap3))
(setq coords (list 
(list 961.086 866.7) 
(list 960.4235 866.7) 
(list 960.4235 866.7103) 
(list 960.4235 866.7206) 
(list 960.4235 866.7308) 
(list 960.4235 866.7411) 
(list 960.4235 866.7514) 
(list 960.4235 866.7617) 
(list 960.4235 866.7719) 
(list 960.4235 866.7822) 
(list 960.4235 866.7925) 
(list 960.4235 866.8028) 
(list 960.4235 866.8131) 
(list 960.4235 866.8233) 
(list 960.4235 866.8336) 
(list 960.4235 866.8439) 
(list 960.4235 866.8542) 
(list 960.4235 866.8644) 
(list 960.4235 866.8747) 
(list 960.4235 866.885) 
(list 960.4235 866.8953) 
(list 960.4235 866.9056) 
(list 960.4235 866.9158) 
(list 960.4235 866.9261) 
(list 960.4235 866.9364) 
(list 960.4235 866.9467) 
(list 960.4235 866.9569) 
(list 960.4235 866.9672) 
(list 960.4235 866.9775) 
(list 960.4235 866.9878) 
(list 960.4235 866.9981) 
(list 960.4235 867.0083) 
(list 960.4235 867.0186) 
(list 960.4235 867.0289) 
(list 960.4235 867.0392) 
(list 960.4235 867.0494) 
(list 960.4235 867.0597) 
(list 960.4235 867.07) 
(list 961.086 867.07)))
(apply 'command (append '("pline") coords '("c")))
(setq tap3 (ssadd (entlast) tap3))
(command "_mirror" (entlast) "" "960,900" "960,901" "No")
(setq tap3 (ssadd (entlast) tap3))
(setq coords (list 
(list 960 867.07) 
(list 960.135 867.07) 
(list 960.135 867.0803) 
(list 960.135 867.0906) 
(list 960.135 867.1008) 
(list 960.135 867.1111) 
(list 960.135 867.1214) 
(list 960.135 867.1317) 
(list 960.135 867.1419) 
(list 960.135 867.1522) 
(list 960.135 867.1625) 
(list 960.135 867.1728) 
(list 960.135 867.1831) 
(list 960.135 867.1933) 
(list 960.135 867.2036) 
(list 960.135 867.2139) 
(list 960.135 867.2242) 
(list 960.135 867.2344) 
(list 960.135 867.2447) 
(list 960.135 867.255) 
(list 960.135 867.2653) 
(list 960.135 867.2756) 
(list 960.135 867.2858) 
(list 960.135 867.2961) 
(list 960.135 867.3064) 
(list 960.135 867.3167) 
(list 960.135 867.3269) 
(list 960.135 867.3372) 
(list 960.135 867.3475) 
(list 960.135 867.3578) 
(list 960.135 867.3681) 
(list 960.135 867.3783) 
(list 960.135 867.3886) 
(list 960.135 867.3989) 
(list 960.135 867.4092) 
(list 960.135 867.4194) 
(list 960.135 867.4297) 
(list 960.135 867.44) 
(list 960 867.44)))
(apply 'command (append '("pline") coords '("c")))
(setq tap3 (ssadd (entlast) tap3))
(command "_mirror" (entlast) "" "960,900" "960,901" "No")
(setq tap3 (ssadd (entlast) tap3))
(setq coords (list 
(list 960.4321 867.07) 
(list 960.4235 867.07) 
(list 960.4236 867.0803) 
(list 960.4234 867.0906) 
(list 960.423 867.1008) 
(list 960.4222 867.1111) 
(list 960.4211 867.1214) 
(list 960.4198 867.1317) 
(list 960.4183 867.1419) 
(list 960.4165 867.1522) 
(list 960.4147 867.1625) 
(list 960.4127 867.1728) 
(list 960.4107 867.1831) 
(list 960.4088 867.1933) 
(list 960.4069 867.2036) 
(list 960.4053 867.2139) 
(list 960.4038 867.2242) 
(list 960.4027 867.2344) 
(list 960.4018 867.2447) 
(list 960.4014 867.255) 
(list 960.4014 867.2653) 
(list 960.4017 867.2756) 
(list 960.4025 867.2858) 
(list 960.4037 867.2961) 
(list 960.4053 867.3064) 
(list 960.4072 867.3167) 
(list 960.4094 867.3269) 
(list 960.4119 867.3372) 
(list 960.4145 867.3475) 
(list 960.4172 867.3578) 
(list 960.42 867.3681) 
(list 960.4226 867.3783) 
(list 960.425 867.3886) 
(list 960.4272 867.3989) 
(list 960.4291 867.4092) 
(list 960.4306 867.4194) 
(list 960.4316 867.4297) 
(list 960.4321 867.44) 
(list 960.4321 867.44)))
(apply 'command (append '("pline") coords '("c")))
(setq tap3 (ssadd (entlast) tap3))
(command "_mirror" (entlast) "" "960,900" "960,901" "No")
(setq tap3 (ssadd (entlast) tap3))
(setq coords (list 
(list 961.086 867.07) 
(list 960.4321 867.07) 
(list 960.4321 867.0803) 
(list 960.4321 867.0906) 
(list 960.4321 867.1008) 
(list 960.4321 867.1111) 
(list 960.4321 867.1214) 
(list 960.4321 867.1317) 
(list 960.4321 867.1419) 
(list 960.4321 867.1522) 
(list 960.4321 867.1625) 
(list 960.4321 867.1728) 
(list 960.4321 867.1831) 
(list 960.4321 867.1933) 
(list 960.4321 867.2036) 
(list 960.4321 867.2139) 
(list 960.4321 867.2242) 
(list 960.4321 867.2344) 
(list 960.4321 867.2447) 
(list 960.4321 867.255) 
(list 960.4321 867.2653) 
(list 960.4321 867.2756) 
(list 960.4321 867.2858) 
(list 960.4321 867.2961) 
(list 960.4321 867.3064) 
(list 960.4321 867.3167) 
(list 960.4321 867.3269) 
(list 960.4321 867.3372) 
(list 960.4321 867.3475) 
(list 960.4321 867.3578) 
(list 960.4321 867.3681) 
(list 960.4321 867.3783) 
(list 960.4321 867.3886) 
(list 960.4321 867.3989) 
(list 960.4321 867.4092) 
(list 960.4321 867.4194) 
(list 960.4321 867.4297) 
(list 960.4321 867.44) 
(list 961.086 867.44)))
(apply 'command (append '("pline") coords '("c")))
(setq tap3 (ssadd (entlast) tap3))
(command "_mirror" (entlast) "" "960,900" "960,901" "No")
(setq tap3 (ssadd (entlast) tap3))
(setq coords (list 
(list 960 867.44) 
(list 960.135 867.44) 
(list 960.135 867.4503) 
(list 960.135 867.4606) 
(list 960.135 867.4708) 
(list 960.135 867.4811) 
(list 960.135 867.4914) 
(list 960.135 867.5017) 
(list 960.135 867.5119) 
(list 960.135 867.5222) 
(list 960.135 867.5325) 
(list 960.135 867.5428) 
(list 960.135 867.5531) 
(list 960.135 867.5633) 
(list 960.135 867.5736) 
(list 960.135 867.5839) 
(list 960.135 867.5942) 
(list 960.135 867.6044) 
(list 960.135 867.6147) 
(list 960.135 867.625) 
(list 960.135 867.6353) 
(list 960.135 867.6456) 
(list 960.135 867.6558) 
(list 960.135 867.6661) 
(list 960.135 867.6764) 
(list 960.135 867.6867) 
(list 960.135 867.6969) 
(list 960.135 867.7072) 
(list 960.135 867.7175) 
(list 960.135 867.7278) 
(list 960.135 867.7381) 
(list 960.135 867.7483) 
(list 960.135 867.7586) 
(list 960.135 867.7689) 
(list 960.135 867.7792) 
(list 960.135 867.7894) 
(list 960.135 867.7997) 
(list 960.135 867.81) 
(list 960 867.81)))
(apply 'command (append '("pline") coords '("c")))
(setq tap3 (ssadd (entlast) tap3))
(command "_mirror" (entlast) "" "960,900" "960,901" "No")
(setq tap3 (ssadd (entlast) tap3))
(setq coords (list 
(list 960.4406 867.44) 
(list 960.4321 867.44) 
(list 960.432 867.4503) 
(list 960.4315 867.4606) 
(list 960.4303 867.4708) 
(list 960.4287 867.4811) 
(list 960.4265 867.4914) 
(list 960.424 867.5017) 
(list 960.421 867.5119) 
(list 960.4178 867.5222) 
(list 960.4144 867.5325) 
(list 960.4109 867.5428) 
(list 960.4074 867.5531) 
(list 960.4041 867.5633) 
(list 960.401 867.5736) 
(list 960.3983 867.5839) 
(list 960.3959 867.5942) 
(list 960.3941 867.6044) 
(list 960.3929 867.6147) 
(list 960.3923 867.625) 
(list 960.3924 867.6353) 
(list 960.3932 867.6456) 
(list 960.3946 867.6558) 
(list 960.3967 867.6661) 
(list 960.3994 867.6764) 
(list 960.4026 867.6867) 
(list 960.4062 867.6969) 
(list 960.4101 867.7072) 
(list 960.4143 867.7175) 
(list 960.4185 867.7278) 
(list 960.4227 867.7381) 
(list 960.4267 867.7483) 
(list 960.4304 867.7586) 
(list 960.4337 867.7689) 
(list 960.4365 867.7792) 
(list 960.4386 867.7894) 
(list 960.44 867.7997) 
(list 960.4406 867.81) 
(list 960.4406 867.81)))
(apply 'command (append '("pline") coords '("c")))
(setq tap3 (ssadd (entlast) tap3))
(command "_mirror" (entlast) "" "960,900" "960,901" "No")
(setq tap3 (ssadd (entlast) tap3))
(setq coords (list 
(list 961.086 867.44) 
(list 960.4406 867.44) 
(list 960.4406 867.4503) 
(list 960.4406 867.4606) 
(list 960.4406 867.4708) 
(list 960.4406 867.4811) 
(list 960.4406 867.4914) 
(list 960.4406 867.5017) 
(list 960.4406 867.5119) 
(list 960.4406 867.5222) 
(list 960.4406 867.5325) 
(list 960.4406 867.5428) 
(list 960.4406 867.5531) 
(list 960.4406 867.5633) 
(list 960.4406 867.5736) 
(list 960.4406 867.5839) 
(list 960.4406 867.5942) 
(list 960.4406 867.6044) 
(list 960.4406 867.6147) 
(list 960.4406 867.625) 
(list 960.4406 867.6353) 
(list 960.4406 867.6456) 
(list 960.4406 867.6558) 
(list 960.4406 867.6661) 
(list 960.4406 867.6764) 
(list 960.4406 867.6867) 
(list 960.4406 867.6969) 
(list 960.4406 867.7072) 
(list 960.4406 867.7175) 
(list 960.4406 867.7278) 
(list 960.4406 867.7381) 
(list 960.4406 867.7483) 
(list 960.4406 867.7586) 
(list 960.4406 867.7689) 
(list 960.4406 867.7792) 
(list 960.4406 867.7894) 
(list 960.4406 867.7997) 
(list 960.4406 867.81) 
(list 961.086 867.81)))
(apply 'command (append '("pline") coords '("c")))
(setq tap3 (ssadd (entlast) tap3))
(command "_mirror" (entlast) "" "960,900" "960,901" "No")
(setq tap3 (ssadd (entlast) tap3))
(setq coords (list 
(list 960 867.81) 
(list 960.135 867.81) 
(list 960.135 867.8203) 
(list 960.135 867.8306) 
(list 960.135 867.8408) 
(list 960.135 867.8511) 
(list 960.135 867.8614) 
(list 960.135 867.8717) 
(list 960.135 867.8819) 
(list 960.135 867.8922) 
(list 960.135 867.9025) 
(list 960.135 867.9128) 
(list 960.135 867.9231) 
(list 960.135 867.9333) 
(list 960.135 867.9436) 
(list 960.135 867.9539) 
(list 960.135 867.9642) 
(list 960.135 867.9744) 
(list 960.135 867.9847) 
(list 960.135 867.995) 
(list 960.135 868.0053) 
(list 960.135 868.0156) 
(list 960.135 868.0258) 
(list 960.135 868.0361) 
(list 960.135 868.0464) 
(list 960.135 868.0567) 
(list 960.135 868.0669) 
(list 960.135 868.0772) 
(list 960.135 868.0875) 
(list 960.135 868.0978) 
(list 960.135 868.1081) 
(list 960.135 868.1183) 
(list 960.135 868.1286) 
(list 960.135 868.1389) 
(list 960.135 868.1492) 
(list 960.135 868.1594) 
(list 960.135 868.1697) 
(list 960.135 868.18) 
(list 960 868.18)))
(apply 'command (append '("pline") coords '("c")))
(setq tap3 (ssadd (entlast) tap3))
(command "_mirror" (entlast) "" "960,900" "960,901" "No")
(setq tap3 (ssadd (entlast) tap3))
(setq coords (list 
(list 960.4491 867.81) 
(list 960.4406 867.81) 
(list 960.4404 867.8203) 
(list 960.4395 867.8306) 
(list 960.4377 867.8408) 
(list 960.4351 867.8511) 
(list 960.4319 867.8614) 
(list 960.4281 867.8717) 
(list 960.4238 867.8819) 
(list 960.4191 867.8922) 
(list 960.4141 867.9025) 
(list 960.4091 867.9128) 
(list 960.4042 867.9231) 
(list 960.3994 867.9333) 
(list 960.3951 867.9436) 
(list 960.3913 867.9539) 
(list 960.3881 867.9642) 
(list 960.3856 867.9744) 
(list 960.384 867.9847) 
(list 960.3833 867.995) 
(list 960.3835 868.0053) 
(list 960.3846 868.0156) 
(list 960.3867 868.0258) 
(list 960.3897 868.0361) 
(list 960.3934 868.0464) 
(list 960.3979 868.0567) 
(list 960.4029 868.0669) 
(list 960.4083 868.0772) 
(list 960.414 868.0875) 
(list 960.4198 868.0978) 
(list 960.4254 868.1081) 
(list 960.4308 868.1183) 
(list 960.4358 868.1286) 
(list 960.4402 868.1389) 
(list 960.4438 868.1492) 
(list 960.4466 868.1594) 
(list 960.4484 868.1697) 
(list 960.4491 868.18) 
(list 960.4491 868.18)))
(apply 'command (append '("pline") coords '("c")))
(setq tap3 (ssadd (entlast) tap3))
(command "_mirror" (entlast) "" "960,900" "960,901" "No")
(setq tap3 (ssadd (entlast) tap3))
(setq coords (list 
(list 961.086 867.81) 
(list 960.4491 867.81) 
(list 960.4491 867.8203) 
(list 960.4491 867.8306) 
(list 960.4491 867.8408) 
(list 960.4491 867.8511) 
(list 960.4491 867.8614) 
(list 960.4491 867.8717) 
(list 960.4491 867.8819) 
(list 960.4491 867.8922) 
(list 960.4491 867.9025) 
(list 960.4491 867.9128) 
(list 960.4491 867.9231) 
(list 960.4491 867.9333) 
(list 960.4491 867.9436) 
(list 960.4491 867.9539) 
(list 960.4491 867.9642) 
(list 960.4491 867.9744) 
(list 960.4491 867.9847) 
(list 960.4491 867.995) 
(list 960.4491 868.0053) 
(list 960.4491 868.0156) 
(list 960.4491 868.0258) 
(list 960.4491 868.0361) 
(list 960.4491 868.0464) 
(list 960.4491 868.0567) 
(list 960.4491 868.0669) 
(list 960.4491 868.0772) 
(list 960.4491 868.0875) 
(list 960.4491 868.0978) 
(list 960.4491 868.1081) 
(list 960.4491 868.1183) 
(list 960.4491 868.1286) 
(list 960.4491 868.1389) 
(list 960.4491 868.1492) 
(list 960.4491 868.1594) 
(list 960.4491 868.1697) 
(list 960.4491 868.18) 
(list 961.086 868.18)))
(apply 'command (append '("pline") coords '("c")))
(setq tap3 (ssadd (entlast) tap3))
(command "_mirror" (entlast) "" "960,900" "960,901" "No")
(setq tap3 (ssadd (entlast) tap3))
(setq coords (list 
(list 960 868.18) 
(list 960.135 868.18) 
(list 960.135 868.1903) 
(list 960.135 868.2006) 
(list 960.135 868.2108) 
(list 960.135 868.2211) 
(list 960.135 868.2314) 
(list 960.135 868.2417) 
(list 960.135 868.2519) 
(list 960.135 868.2622) 
(list 960.135 868.2725) 
(list 960.135 868.2828) 
(list 960.135 868.2931) 
(list 960.135 868.3033) 
(list 960.135 868.3136) 
(list 960.135 868.3239) 
(list 960.135 868.3342) 
(list 960.135 868.3444) 
(list 960.135 868.3547) 
(list 960.135 868.365) 
(list 960.135 868.3753) 
(list 960.135 868.3856) 
(list 960.135 868.3958) 
(list 960.135 868.4061) 
(list 960.135 868.4164) 
(list 960.135 868.4267) 
(list 960.135 868.4369) 
(list 960.135 868.4472) 
(list 960.135 868.4575) 
(list 960.135 868.4678) 
(list 960.135 868.4781) 
(list 960.135 868.4883) 
(list 960.135 868.4986) 
(list 960.135 868.5089) 
(list 960.135 868.5192) 
(list 960.135 868.5294) 
(list 960.135 868.5397) 
(list 960.135 868.55) 
(list 960 868.55)))
(apply 'command (append '("pline") coords '("c")))
(setq tap3 (ssadd (entlast) tap3))
(command "_mirror" (entlast) "" "960,900" "960,901" "No")
(setq tap3 (ssadd (entlast) tap3))
(setq coords (list 
(list 960.4577 868.18) 
(list 960.4491 868.18) 
(list 960.4488 868.1903) 
(list 960.4475 868.2006) 
(list 960.445 868.2108) 
(list 960.4416 868.2211) 
(list 960.4373 868.2314) 
(list 960.4322 868.2417) 
(list 960.4265 868.2519) 
(list 960.4203 868.2622) 
(list 960.4139 868.2725) 
(list 960.4073 868.2828) 
(list 960.4009 868.2931) 
(list 960.3948 868.3033) 
(list 960.3892 868.3136) 
(list 960.3842 868.3239) 
(list 960.3802 868.3342) 
(list 960.3771 868.3444) 
(list 960.375 868.3547) 
(list 960.3742 868.365) 
(list 960.3746 868.3753) 
(list 960.3761 868.3856) 
(list 960.3788 868.3958) 
(list 960.3827 868.4061) 
(list 960.3875 868.4164) 
(list 960.3932 868.4267) 
(list 960.3996 868.4369) 
(list 960.4065 868.4472) 
(list 960.4137 868.4575) 
(list 960.421 868.4678) 
(list 960.4282 868.4781) 
(list 960.435 868.4883) 
(list 960.4412 868.4986) 
(list 960.4467 868.5089) 
(list 960.4512 868.5192) 
(list 960.4546 868.5294) 
(list 960.4568 868.5397) 
(list 960.4577 868.55) 
(list 960.4577 868.55)))
(apply 'command (append '("pline") coords '("c")))
(setq tap3 (ssadd (entlast) tap3))
(command "_mirror" (entlast) "" "960,900" "960,901" "No")
(setq tap3 (ssadd (entlast) tap3))
(setq coords (list 
(list 961.086 868.18) 
(list 960.4577 868.18) 
(list 960.4577 868.1903) 
(list 960.4577 868.2006) 
(list 960.4577 868.2108) 
(list 960.4577 868.2211) 
(list 960.4577 868.2314) 
(list 960.4577 868.2417) 
(list 960.4577 868.2519) 
(list 960.4577 868.2622) 
(list 960.4577 868.2725) 
(list 960.4577 868.2828) 
(list 960.4577 868.2931) 
(list 960.4577 868.3033) 
(list 960.4577 868.3136) 
(list 960.4577 868.3239) 
(list 960.4577 868.3342) 
(list 960.4577 868.3444) 
(list 960.4577 868.3547) 
(list 960.4577 868.365) 
(list 960.4577 868.3753) 
(list 960.4577 868.3856) 
(list 960.4577 868.3958) 
(list 960.4577 868.4061) 
(list 960.4577 868.4164) 
(list 960.4577 868.4267) 
(list 960.4577 868.4369) 
(list 960.4577 868.4472) 
(list 960.4577 868.4575) 
(list 960.4577 868.4678) 
(list 960.4577 868.4781) 
(list 960.4577 868.4883) 
(list 960.4577 868.4986) 
(list 960.4577 868.5089) 
(list 960.4577 868.5192) 
(list 960.4577 868.5294) 
(list 960.4577 868.5397) 
(list 960.4577 868.55) 
(list 961.086 868.55)))
(apply 'command (append '("pline") coords '("c")))
(setq tap3 (ssadd (entlast) tap3))
(command "_mirror" (entlast) "" "960,900" "960,901" "No")
(setq tap3 (ssadd (entlast) tap3))
(setq coords (list 
(list 960 868.55) 
(list 960.135 868.55) 
(list 960.135 868.5603) 
(list 960.135 868.5706) 
(list 960.135 868.5808) 
(list 960.135 868.5911) 
(list 960.135 868.6014) 
(list 960.135 868.6117) 
(list 960.135 868.6219) 
(list 960.135 868.6322) 
(list 960.135 868.6425) 
(list 960.135 868.6528) 
(list 960.135 868.6631) 
(list 960.135 868.6733) 
(list 960.135 868.6836) 
(list 960.135 868.6939) 
(list 960.135 868.7042) 
(list 960.135 868.7144) 
(list 960.135 868.7247) 
(list 960.135 868.735) 
(list 960.135 868.7453) 
(list 960.135 868.7556) 
(list 960.135 868.7658) 
(list 960.135 868.7761) 
(list 960.135 868.7864) 
(list 960.135 868.7967) 
(list 960.135 868.8069) 
(list 960.135 868.8172) 
(list 960.135 868.8275) 
(list 960.135 868.8378) 
(list 960.135 868.8481) 
(list 960.135 868.8583) 
(list 960.135 868.8686) 
(list 960.135 868.8789) 
(list 960.135 868.8892) 
(list 960.135 868.8994) 
(list 960.135 868.9097) 
(list 960.135 868.92) 
(list 960 868.92)))
(apply 'command (append '("pline") coords '("c")))
(setq tap3 (ssadd (entlast) tap3))
(command "_mirror" (entlast) "" "960,900" "960,901" "No")
(setq tap3 (ssadd (entlast) tap3))
(setq coords (list 
(list 960.4662 868.55) 
(list 960.4577 868.55) 
(list 960.4572 868.5603) 
(list 960.4555 868.5706) 
(list 960.4524 868.5808) 
(list 960.4481 868.5911) 
(list 960.4427 868.6014) 
(list 960.4364 868.6117) 
(list 960.4292 868.6219) 
(list 960.4216 868.6322) 
(list 960.4136 868.6425) 
(list 960.4055 868.6528) 
(list 960.3976 868.6631) 
(list 960.3901 868.6733) 
(list 960.3832 868.6836) 
(list 960.3772 868.6939) 
(list 960.3723 868.7042) 
(list 960.3685 868.7144) 
(list 960.3661 868.7247) 
(list 960.3651 868.735) 
(list 960.3656 868.7453) 
(list 960.3676 868.7556) 
(list 960.371 868.7658) 
(list 960.3757 868.7761) 
(list 960.3816 868.7864) 
(list 960.3886 868.7967) 
(list 960.3963 868.8069) 
(list 960.4047 868.8172) 
(list 960.4135 868.8275) 
(list 960.4223 868.8378) 
(list 960.4309 868.8481) 
(list 960.4391 868.8583) 
(list 960.4466 868.8686) 
(list 960.4531 868.8789) 
(list 960.4585 868.8892) 
(list 960.4626 868.8994) 
(list 960.4652 868.9097) 
(list 960.4662 868.92) 
(list 960.4662 868.92)))
(apply 'command (append '("pline") coords '("c")))
(setq tap3 (ssadd (entlast) tap3))
(command "_mirror" (entlast) "" "960,900" "960,901" "No")
(setq tap3 (ssadd (entlast) tap3))
(setq coords (list 
(list 961.086 868.55) 
(list 960.4662 868.55) 
(list 960.4662 868.5603) 
(list 960.4662 868.5706) 
(list 960.4662 868.5808) 
(list 960.4662 868.5911) 
(list 960.4662 868.6014) 
(list 960.4662 868.6117) 
(list 960.4662 868.6219) 
(list 960.4662 868.6322) 
(list 960.4662 868.6425) 
(list 960.4662 868.6528) 
(list 960.4662 868.6631) 
(list 960.4662 868.6733) 
(list 960.4662 868.6836) 
(list 960.4662 868.6939) 
(list 960.4662 868.7042) 
(list 960.4662 868.7144) 
(list 960.4662 868.7247) 
(list 960.4662 868.735) 
(list 960.4662 868.7453) 
(list 960.4662 868.7556) 
(list 960.4662 868.7658) 
(list 960.4662 868.7761) 
(list 960.4662 868.7864) 
(list 960.4662 868.7967) 
(list 960.4662 868.8069) 
(list 960.4662 868.8172) 
(list 960.4662 868.8275) 
(list 960.4662 868.8378) 
(list 960.4662 868.8481) 
(list 960.4662 868.8583) 
(list 960.4662 868.8686) 
(list 960.4662 868.8789) 
(list 960.4662 868.8892) 
(list 960.4662 868.8994) 
(list 960.4662 868.9097) 
(list 960.4662 868.92) 
(list 961.086 868.92)))
(apply 'command (append '("pline") coords '("c")))
(setq tap3 (ssadd (entlast) tap3))
(command "_mirror" (entlast) "" "960,900" "960,901" "No")
(setq tap3 (ssadd (entlast) tap3))
(setq coords (list 
(list 960 868.92) 
(list 960.135 868.92) 
(list 960.135 868.9303) 
(list 960.135 868.9406) 
(list 960.135 868.9508) 
(list 960.135 868.9611) 
(list 960.135 868.9714) 
(list 960.135 868.9817) 
(list 960.135 868.9919) 
(list 960.135 869.0022) 
(list 960.135 869.0125) 
(list 960.135 869.0228) 
(list 960.135 869.0331) 
(list 960.135 869.0433) 
(list 960.135 869.0536) 
(list 960.135 869.0639) 
(list 960.135 869.0742) 
(list 960.135 869.0844) 
(list 960.135 869.0947) 
(list 960.135 869.105) 
(list 960.135 869.1153) 
(list 960.135 869.1256) 
(list 960.135 869.1358) 
(list 960.135 869.1461) 
(list 960.135 869.1564) 
(list 960.135 869.1667) 
(list 960.135 869.1769) 
(list 960.135 869.1872) 
(list 960.135 869.1975) 
(list 960.135 869.2078) 
(list 960.135 869.2181) 
(list 960.135 869.2283) 
(list 960.135 869.2386) 
(list 960.135 869.2489) 
(list 960.135 869.2592) 
(list 960.135 869.2694) 
(list 960.135 869.2797) 
(list 960.135 869.29) 
(list 960 869.29)))
(apply 'command (append '("pline") coords '("c")))
(setq tap3 (ssadd (entlast) tap3))
(command "_mirror" (entlast) "" "960,900" "960,901" "No")
(setq tap3 (ssadd (entlast) tap3))
(setq coords (list 
(list 960.4747 868.92) 
(list 960.4662 868.92) 
(list 960.4656 868.9303) 
(list 960.4635 868.9406) 
(list 960.4597 868.9508) 
(list 960.4546 868.9611) 
(list 960.4481 868.9714) 
(list 960.4405 868.9817) 
(list 960.432 868.9919) 
(list 960.4228 869.0022) 
(list 960.4133 869.0125) 
(list 960.4037 869.0228) 
(list 960.3943 869.0331) 
(list 960.3854 869.0433) 
(list 960.3773 869.0536) 
(list 960.3702 869.0639) 
(list 960.3644 869.0742) 
(list 960.36 869.0844) 
(list 960.3572 869.0947) 
(list 960.3561 869.105) 
(list 960.3567 869.1153) 
(list 960.359 869.1256) 
(list 960.3631 869.1358) 
(list 960.3687 869.1461) 
(list 960.3757 869.1564) 
(list 960.3839 869.1667) 
(list 960.3931 869.1769) 
(list 960.4029 869.1872) 
(list 960.4132 869.1975) 
(list 960.4235 869.2078) 
(list 960.4337 869.2181) 
(list 960.4432 869.2283) 
(list 960.452 869.2386) 
(list 960.4596 869.2489) 
(list 960.4659 869.2592) 
(list 960.4706 869.2694) 
(list 960.4736 869.2797) 
(list 960.4747 869.29) 
(list 960.4747 869.29)))
(apply 'command (append '("pline") coords '("c")))
(setq tap3 (ssadd (entlast) tap3))
(command "_mirror" (entlast) "" "960,900" "960,901" "No")
(setq tap3 (ssadd (entlast) tap3))
(setq coords (list 
(list 961.086 868.92) 
(list 960.4747 868.92) 
(list 960.4747 868.9303) 
(list 960.4747 868.9406) 
(list 960.4747 868.9508) 
(list 960.4747 868.9611) 
(list 960.4747 868.9714) 
(list 960.4747 868.9817) 
(list 960.4747 868.9919) 
(list 960.4747 869.0022) 
(list 960.4747 869.0125) 
(list 960.4747 869.0228) 
(list 960.4747 869.0331) 
(list 960.4747 869.0433) 
(list 960.4747 869.0536) 
(list 960.4747 869.0639) 
(list 960.4747 869.0742) 
(list 960.4747 869.0844) 
(list 960.4747 869.0947) 
(list 960.4747 869.105) 
(list 960.4747 869.1153) 
(list 960.4747 869.1256) 
(list 960.4747 869.1358) 
(list 960.4747 869.1461) 
(list 960.4747 869.1564) 
(list 960.4747 869.1667) 
(list 960.4747 869.1769) 
(list 960.4747 869.1872) 
(list 960.4747 869.1975) 
(list 960.4747 869.2078) 
(list 960.4747 869.2181) 
(list 960.4747 869.2283) 
(list 960.4747 869.2386) 
(list 960.4747 869.2489) 
(list 960.4747 869.2592) 
(list 960.4747 869.2694) 
(list 960.4747 869.2797) 
(list 960.4747 869.29) 
(list 961.086 869.29)))
(apply 'command (append '("pline") coords '("c")))
(setq tap3 (ssadd (entlast) tap3))
(command "_mirror" (entlast) "" "960,900" "960,901" "No")
(setq tap3 (ssadd (entlast) tap3))
(setq coords (list 
(list 960 869.29) 
(list 960.135 869.29) 
(list 960.135 869.3003) 
(list 960.135 869.3106) 
(list 960.135 869.3208) 
(list 960.135 869.3311) 
(list 960.135 869.3414) 
(list 960.135 869.3517) 
(list 960.135 869.3619) 
(list 960.135 869.3722) 
(list 960.135 869.3825) 
(list 960.135 869.3928) 
(list 960.135 869.4031) 
(list 960.135 869.4133) 
(list 960.135 869.4236) 
(list 960.135 869.4339) 
(list 960.135 869.4442) 
(list 960.135 869.4544) 
(list 960.135 869.4647) 
(list 960.135 869.475) 
(list 960.135 869.4853) 
(list 960.135 869.4956) 
(list 960.135 869.5058) 
(list 960.135 869.5161) 
(list 960.135 869.5264) 
(list 960.135 869.5367) 
(list 960.135 869.5469) 
(list 960.135 869.5572) 
(list 960.135 869.5675) 
(list 960.135 869.5778) 
(list 960.135 869.5881) 
(list 960.135 869.5983) 
(list 960.135 869.6086) 
(list 960.135 869.6189) 
(list 960.135 869.6292) 
(list 960.135 869.6394) 
(list 960.135 869.6497) 
(list 960.135 869.66) 
(list 960 869.66)))
(apply 'command (append '("pline") coords '("c")))
(setq tap3 (ssadd (entlast) tap3))
(command "_mirror" (entlast) "" "960,900" "960,901" "No")
(setq tap3 (ssadd (entlast) tap3))
(setq coords (list 
(list 960.4833 869.29) 
(list 960.4747 869.29) 
(list 960.474 869.3003) 
(list 960.4715 869.3106) 
(list 960.4671 869.3208) 
(list 960.461 869.3311) 
(list 960.4535 869.3414) 
(list 960.4446 869.3517) 
(list 960.4347 869.3619) 
(list 960.4241 869.3722) 
(list 960.4131 869.3825) 
(list 960.4019 869.3928) 
(list 960.3911 869.4031) 
(list 960.3808 869.4133) 
(list 960.3714 869.4236) 
(list 960.3632 869.4339) 
(list 960.3565 869.4442) 
(list 960.3515 869.4544) 
(list 960.3483 869.4647) 
(list 960.347 869.475) 
(list 960.3478 869.4853) 
(list 960.3505 869.4956) 
(list 960.3552 869.5058) 
(list 960.3617 869.5161) 
(list 960.3698 869.5264) 
(list 960.3792 869.5367) 
(list 960.3898 869.5469) 
(list 960.4011 869.5572) 
(list 960.4129 869.5675) 
(list 960.4248 869.5778) 
(list 960.4364 869.5881) 
(list 960.4474 869.5983) 
(list 960.4574 869.6086) 
(list 960.4661 869.6189) 
(list 960.4732 869.6292) 
(list 960.4786 869.6394) 
(list 960.482 869.6497) 
(list 960.4833 869.66) 
(list 960.4833 869.66)))
(apply 'command (append '("pline") coords '("c")))
(setq tap3 (ssadd (entlast) tap3))
(command "_mirror" (entlast) "" "960,900" "960,901" "No")
(setq tap3 (ssadd (entlast) tap3))
(setq coords (list 
(list 961.086 869.29) 
(list 960.4833 869.29) 
(list 960.4833 869.3003) 
(list 960.4833 869.3106) 
(list 960.4833 869.3208) 
(list 960.4833 869.3311) 
(list 960.4833 869.3414) 
(list 960.4833 869.3517) 
(list 960.4833 869.3619) 
(list 960.4833 869.3722) 
(list 960.4833 869.3825) 
(list 960.4833 869.3928) 
(list 960.4833 869.4031) 
(list 960.4833 869.4133) 
(list 960.4833 869.4236) 
(list 960.4833 869.4339) 
(list 960.4833 869.4442) 
(list 960.4833 869.4544) 
(list 960.4833 869.4647) 
(list 960.4833 869.475) 
(list 960.4833 869.4853) 
(list 960.4833 869.4956) 
(list 960.4833 869.5058) 
(list 960.4833 869.5161) 
(list 960.4833 869.5264) 
(list 960.4833 869.5367) 
(list 960.4833 869.5469) 
(list 960.4833 869.5572) 
(list 960.4833 869.5675) 
(list 960.4833 869.5778) 
(list 960.4833 869.5881) 
(list 960.4833 869.5983) 
(list 960.4833 869.6086) 
(list 960.4833 869.6189) 
(list 960.4833 869.6292) 
(list 960.4833 869.6394) 
(list 960.4833 869.6497) 
(list 960.4833 869.66) 
(list 961.086 869.66)))
(apply 'command (append '("pline") coords '("c")))
(setq tap3 (ssadd (entlast) tap3))
(command "_mirror" (entlast) "" "960,900" "960,901" "No")
(setq tap3 (ssadd (entlast) tap3))
(setq coords (list 
(list 960 869.66) 
(list 960.135 869.66) 
(list 960.135 869.6703) 
(list 960.135 869.6806) 
(list 960.135 869.6908) 
(list 960.135 869.7011) 
(list 960.135 869.7114) 
(list 960.135 869.7217) 
(list 960.135 869.7319) 
(list 960.135 869.7422) 
(list 960.135 869.7525) 
(list 960.135 869.7628) 
(list 960.135 869.7731) 
(list 960.135 869.7833) 
(list 960.135 869.7936) 
(list 960.135 869.8039) 
(list 960.135 869.8142) 
(list 960.135 869.8244) 
(list 960.135 869.8347) 
(list 960.135 869.845) 
(list 960.135 869.8553) 
(list 960.135 869.8656) 
(list 960.135 869.8758) 
(list 960.135 869.8861) 
(list 960.135 869.8964) 
(list 960.135 869.9067) 
(list 960.135 869.9169) 
(list 960.135 869.9272) 
(list 960.135 869.9375) 
(list 960.135 869.9478) 
(list 960.135 869.9581) 
(list 960.135 869.9683) 
(list 960.135 869.9786) 
(list 960.135 869.9889) 
(list 960.135 869.9992) 
(list 960.135 870.0094) 
(list 960.135 870.0197) 
(list 960.135 870.03) 
(list 960 870.03)))
(apply 'command (append '("pline") coords '("c")))
(setq tap3 (ssadd (entlast) tap3))
(command "_mirror" (entlast) "" "960,900" "960,901" "No")
(setq tap3 (ssadd (entlast) tap3))
(setq coords (list 
(list 960.4918 869.66) 
(list 960.4833 869.66) 
(list 960.4824 869.6703) 
(list 960.4795 869.6806) 
(list 960.4744 869.6908) 
(list 960.4675 869.7011) 
(list 960.4589 869.7114) 
(list 960.4488 869.7217) 
(list 960.4375 869.7319) 
(list 960.4254 869.7422) 
(list 960.4128 869.7525) 
(list 960.4001 869.7628) 
(list 960.3878 869.7731) 
(list 960.3761 869.7833) 
(list 960.3655 869.7936) 
(list 960.3562 869.8039) 
(list 960.3486 869.8142) 
(list 960.3429 869.8244) 
(list 960.3393 869.8347) 
(list 960.3379 869.845) 
(list 960.3388 869.8553) 
(list 960.342 869.8656) 
(list 960.3473 869.8758) 
(list 960.3547 869.8861) 
(list 960.3638 869.8964) 
(list 960.3746 869.9067) 
(list 960.3865 869.9169) 
(list 960.3993 869.9272) 
(list 960.4127 869.9375) 
(list 960.4261 869.9478) 
(list 960.4392 869.9581) 
(list 960.4515 869.9683) 
(list 960.4628 869.9786) 
(list 960.4726 869.9889) 
(list 960.4806 869.9992) 
(list 960.4866 870.0094) 
(list 960.4904 870.0197) 
(list 960.4918 870.03) 
(list 960.4918 870.03)))
(apply 'command (append '("pline") coords '("c")))
(setq tap3 (ssadd (entlast) tap3))
(command "_mirror" (entlast) "" "960,900" "960,901" "No")
(setq tap3 (ssadd (entlast) tap3))
(setq coords (list 
(list 961.086 869.66) 
(list 960.4918 869.66) 
(list 960.4918 869.6703) 
(list 960.4918 869.6806) 
(list 960.4918 869.6908) 
(list 960.4918 869.7011) 
(list 960.4918 869.7114) 
(list 960.4918 869.7217) 
(list 960.4918 869.7319) 
(list 960.4918 869.7422) 
(list 960.4918 869.7525) 
(list 960.4918 869.7628) 
(list 960.4918 869.7731) 
(list 960.4918 869.7833) 
(list 960.4918 869.7936) 
(list 960.4918 869.8039) 
(list 960.4918 869.8142) 
(list 960.4918 869.8244) 
(list 960.4918 869.8347) 
(list 960.4918 869.845) 
(list 960.4918 869.8553) 
(list 960.4918 869.8656) 
(list 960.4918 869.8758) 
(list 960.4918 869.8861) 
(list 960.4918 869.8964) 
(list 960.4918 869.9067) 
(list 960.4918 869.9169) 
(list 960.4918 869.9272) 
(list 960.4918 869.9375) 
(list 960.4918 869.9478) 
(list 960.4918 869.9581) 
(list 960.4918 869.9683) 
(list 960.4918 869.9786) 
(list 960.4918 869.9889) 
(list 960.4918 869.9992) 
(list 960.4918 870.0094) 
(list 960.4918 870.0197) 
(list 960.4918 870.03) 
(list 961.086 870.03)))
(apply 'command (append '("pline") coords '("c")))
(setq tap3 (ssadd (entlast) tap3))
(command "_mirror" (entlast) "" "960,900" "960,901" "No")
(setq tap3 (ssadd (entlast) tap3))
(setq coords (list 
(list 960 870.03) 
(list 960.135 870.03) 
(list 960.135 870.0403) 
(list 960.135 870.0506) 
(list 960.135 870.0608) 
(list 960.135 870.0711) 
(list 960.135 870.0814) 
(list 960.135 870.0917) 
(list 960.135 870.1019) 
(list 960.135 870.1122) 
(list 960.135 870.1225) 
(list 960.135 870.1328) 
(list 960.135 870.1431) 
(list 960.135 870.1533) 
(list 960.135 870.1636) 
(list 960.135 870.1739) 
(list 960.135 870.1842) 
(list 960.135 870.1944) 
(list 960.135 870.2047) 
(list 960.135 870.215) 
(list 960.135 870.2253) 
(list 960.135 870.2356) 
(list 960.135 870.2458) 
(list 960.135 870.2561) 
(list 960.135 870.2664) 
(list 960.135 870.2767) 
(list 960.135 870.2869) 
(list 960.135 870.2972) 
(list 960.135 870.3075) 
(list 960.135 870.3178) 
(list 960.135 870.3281) 
(list 960.135 870.3383) 
(list 960.135 870.3486) 
(list 960.135 870.3589) 
(list 960.135 870.3692) 
(list 960.135 870.3794) 
(list 960.135 870.3897) 
(list 960.135 870.4) 
(list 960 870.4)))
(apply 'command (append '("pline") coords '("c")))
(setq tap3 (ssadd (entlast) tap3))
(command "_mirror" (entlast) "" "960,900" "960,901" "No")
(setq tap3 (ssadd (entlast) tap3))
(setq coords (list 
(list 960.5003 870.03) 
(list 960.4918 870.03) 
(list 960.4908 870.0403) 
(list 960.4875 870.0506) 
(list 960.4818 870.0608) 
(list 960.474 870.0711) 
(list 960.4643 870.0814) 
(list 960.4529 870.0917) 
(list 960.4402 870.1019) 
(list 960.4266 870.1122) 
(list 960.4125 870.1225) 
(list 960.3983 870.1328) 
(list 960.3845 870.1431) 
(list 960.3714 870.1533) 
(list 960.3596 870.1636) 
(list 960.3492 870.1739) 
(list 960.3407 870.1842) 
(list 960.3344 870.1944) 
(list 960.3304 870.2047) 
(list 960.3289 870.215) 
(list 960.3299 870.2253) 
(list 960.3334 870.2356) 
(list 960.3394 870.2458) 
(list 960.3476 870.2561) 
(list 960.3579 870.2664) 
(list 960.3699 870.2767) 
(list 960.3832 870.2869) 
(list 960.3976 870.2972) 
(list 960.4124 870.3075) 
(list 960.4273 870.3178) 
(list 960.4419 870.3281) 
(list 960.4556 870.3383) 
(list 960.4682 870.3486) 
(list 960.479 870.3589) 
(list 960.4879 870.3692) 
(list 960.4946 870.3794) 
(list 960.4988 870.3897) 
(list 960.5003 870.4) 
(list 960.5003 870.4)))
(apply 'command (append '("pline") coords '("c")))
(setq tap3 (ssadd (entlast) tap3))
(command "_mirror" (entlast) "" "960,900" "960,901" "No")
(setq tap3 (ssadd (entlast) tap3))
(setq coords (list 
(list 961.086 870.03) 
(list 960.5003 870.03) 
(list 960.5003 870.0403) 
(list 960.5003 870.0506) 
(list 960.5003 870.0608) 
(list 960.5003 870.0711) 
(list 960.5003 870.0814) 
(list 960.5003 870.0917) 
(list 960.5003 870.1019) 
(list 960.5003 870.1122) 
(list 960.5003 870.1225) 
(list 960.5003 870.1328) 
(list 960.5003 870.1431) 
(list 960.5003 870.1533) 
(list 960.5003 870.1636) 
(list 960.5003 870.1739) 
(list 960.5003 870.1842) 
(list 960.5003 870.1944) 
(list 960.5003 870.2047) 
(list 960.5003 870.215) 
(list 960.5003 870.2253) 
(list 960.5003 870.2356) 
(list 960.5003 870.2458) 
(list 960.5003 870.2561) 
(list 960.5003 870.2664) 
(list 960.5003 870.2767) 
(list 960.5003 870.2869) 
(list 960.5003 870.2972) 
(list 960.5003 870.3075) 
(list 960.5003 870.3178) 
(list 960.5003 870.3281) 
(list 960.5003 870.3383) 
(list 960.5003 870.3486) 
(list 960.5003 870.3589) 
(list 960.5003 870.3692) 
(list 960.5003 870.3794) 
(list 960.5003 870.3897) 
(list 960.5003 870.4) 
(list 961.086 870.4)))
(apply 'command (append '("pline") coords '("c")))
(setq tap3 (ssadd (entlast) tap3))
(command "_mirror" (entlast) "" "960,900" "960,901" "No")
(setq tap3 (ssadd (entlast) tap3))
(setq coords (list 
(list 960 870.4) 
(list 960.135 870.4) 
(list 960.135 870.4103) 
(list 960.135 870.4206) 
(list 960.135 870.4308) 
(list 960.135 870.4411) 
(list 960.135 870.4514) 
(list 960.135 870.4617) 
(list 960.135 870.4719) 
(list 960.135 870.4822) 
(list 960.135 870.4925) 
(list 960.135 870.5028) 
(list 960.135 870.5131) 
(list 960.135 870.5233) 
(list 960.135 870.5336) 
(list 960.135 870.5439) 
(list 960.135 870.5542) 
(list 960.135 870.5644) 
(list 960.135 870.5747) 
(list 960.135 870.585) 
(list 960.135 870.5953) 
(list 960.135 870.6056) 
(list 960.135 870.6158) 
(list 960.135 870.6261) 
(list 960.135 870.6364) 
(list 960.135 870.6467) 
(list 960.135 870.6569) 
(list 960.135 870.6672) 
(list 960.135 870.6775) 
(list 960.135 870.6878) 
(list 960.135 870.6981) 
(list 960.135 870.7083) 
(list 960.135 870.7186) 
(list 960.135 870.7289) 
(list 960.135 870.7392) 
(list 960.135 870.7494) 
(list 960.135 870.7597) 
(list 960.135 870.77) 
(list 960 870.77)))
(apply 'command (append '("pline") coords '("c")))
(setq tap3 (ssadd (entlast) tap3))
(command "_mirror" (entlast) "" "960,900" "960,901" "No")
(setq tap3 (ssadd (entlast) tap3))
(setq coords (list 
(list 960.5089 870.4) 
(list 960.5003 870.4) 
(list 960.4992 870.4103) 
(list 960.4955 870.4206) 
(list 960.4892 870.4308) 
(list 960.4805 870.4411) 
(list 960.4696 870.4514) 
(list 960.457 870.4617) 
(list 960.443 870.4719) 
(list 960.4279 870.4822) 
(list 960.4123 870.4925) 
(list 960.3966 870.5028) 
(list 960.3812 870.5131) 
(list 960.3668 870.5233) 
(list 960.3536 870.5336) 
(list 960.3422 870.5439) 
(list 960.3328 870.5542) 
(list 960.3258 870.5644) 
(list 960.3215 870.5747) 
(list 960.3198 870.585) 
(list 960.321 870.5953) 
(list 960.3249 870.6056) 
(list 960.3315 870.6158) 
(list 960.3406 870.6261) 
(list 960.352 870.6364) 
(list 960.3652 870.6467) 
(list 960.38 870.6569) 
(list 960.3958 870.6672) 
(list 960.4121 870.6775) 
(list 960.4286 870.6878) 
(list 960.4446 870.6981) 
(list 960.4598 870.7083) 
(list 960.4735 870.7186) 
(list 960.4855 870.7289) 
(list 960.4953 870.7392) 
(list 960.5026 870.7494) 
(list 960.5072 870.7597) 
(list 960.5089 870.77) 
(list 960.5089 870.77)))
(apply 'command (append '("pline") coords '("c")))
(setq tap3 (ssadd (entlast) tap3))
(command "_mirror" (entlast) "" "960,900" "960,901" "No")
(setq tap3 (ssadd (entlast) tap3))
(setq coords (list 
(list 961.086 870.4) 
(list 960.5089 870.4) 
(list 960.5089 870.4103) 
(list 960.5089 870.4206) 
(list 960.5089 870.4308) 
(list 960.5089 870.4411) 
(list 960.5089 870.4514) 
(list 960.5089 870.4617) 
(list 960.5089 870.4719) 
(list 960.5089 870.4822) 
(list 960.5089 870.4925) 
(list 960.5089 870.5028) 
(list 960.5089 870.5131) 
(list 960.5089 870.5233) 
(list 960.5089 870.5336) 
(list 960.5089 870.5439) 
(list 960.5089 870.5542) 
(list 960.5089 870.5644) 
(list 960.5089 870.5747) 
(list 960.5089 870.585) 
(list 960.5089 870.5953) 
(list 960.5089 870.6056) 
(list 960.5089 870.6158) 
(list 960.5089 870.6261) 
(list 960.5089 870.6364) 
(list 960.5089 870.6467) 
(list 960.5089 870.6569) 
(list 960.5089 870.6672) 
(list 960.5089 870.6775) 
(list 960.5089 870.6878) 
(list 960.5089 870.6981) 
(list 960.5089 870.7083) 
(list 960.5089 870.7186) 
(list 960.5089 870.7289) 
(list 960.5089 870.7392) 
(list 960.5089 870.7494) 
(list 960.5089 870.7597) 
(list 960.5089 870.77) 
(list 961.086 870.77)))
(apply 'command (append '("pline") coords '("c")))
(setq tap3 (ssadd (entlast) tap3))
(command "_mirror" (entlast) "" "960,900" "960,901" "No")
(setq tap3 (ssadd (entlast) tap3))
(setq coords (list 
(list 960 870.77) 
(list 960.135 870.77) 
(list 960.135 870.7803) 
(list 960.135 870.7906) 
(list 960.135 870.8008) 
(list 960.135 870.8111) 
(list 960.135 870.8214) 
(list 960.135 870.8317) 
(list 960.135 870.8419) 
(list 960.135 870.8522) 
(list 960.135 870.8625) 
(list 960.135 870.8728) 
(list 960.135 870.8831) 
(list 960.135 870.8933) 
(list 960.135 870.9036) 
(list 960.135 870.9139) 
(list 960.135 870.9242) 
(list 960.135 870.9344) 
(list 960.135 870.9447) 
(list 960.135 870.955) 
(list 960.135 870.9653) 
(list 960.135 870.9756) 
(list 960.135 870.9858) 
(list 960.135 870.9961) 
(list 960.135 871.0064) 
(list 960.135 871.0167) 
(list 960.135 871.0269) 
(list 960.135 871.0372) 
(list 960.135 871.0475) 
(list 960.135 871.0578) 
(list 960.135 871.0681) 
(list 960.135 871.0783) 
(list 960.135 871.0886) 
(list 960.135 871.0989) 
(list 960.135 871.1092) 
(list 960.135 871.1194) 
(list 960.135 871.1297) 
(list 960.135 871.14) 
(list 960 871.14)))
(apply 'command (append '("pline") coords '("c")))
(setq tap3 (ssadd (entlast) tap3))
(command "_mirror" (entlast) "" "960,900" "960,901" "No")
(setq tap3 (ssadd (entlast) tap3))
(setq coords (list 
(list 960.5174 870.77) 
(list 960.5089 870.77) 
(list 960.5076 870.7803) 
(list 960.5035 870.7906) 
(list 960.4965 870.8008) 
(list 960.4869 870.8111) 
(list 960.475 870.8214) 
(list 960.4612 870.8317) 
(list 960.4457 870.8419) 
(list 960.4292 870.8522) 
(list 960.412 870.8625) 
(list 960.3948 870.8728) 
(list 960.378 870.8831) 
(list 960.3621 870.8933) 
(list 960.3477 870.9036) 
(list 960.3352 870.9139) 
(list 960.3249 870.9242) 
(list 960.3173 870.9344) 
(list 960.3125 870.9447) 
(list 960.3107 870.955) 
(list 960.312 870.9653) 
(list 960.3164 870.9756) 
(list 960.3236 870.9858) 
(list 960.3336 870.9961) 
(list 960.3461 871.0064) 
(list 960.3606 871.0167) 
(list 960.3767 871.0269) 
(list 960.394 871.0372) 
(list 960.4119 871.0475) 
(list 960.4299 871.0578) 
(list 960.4474 871.0681) 
(list 960.4639 871.0783) 
(list 960.4789 871.0886) 
(list 960.492 871.0989) 
(list 960.5026 871.1092) 
(list 960.5106 871.1194) 
(list 960.5156 871.1297) 
(list 960.5174 871.14) 
(list 960.5174 871.14)))
(apply 'command (append '("pline") coords '("c")))
(setq tap3 (ssadd (entlast) tap3))
(command "_mirror" (entlast) "" "960,900" "960,901" "No")
(setq tap3 (ssadd (entlast) tap3))
(setq coords (list 
(list 961.086 870.77) 
(list 960.5174 870.77) 
(list 960.5174 870.7803) 
(list 960.5174 870.7906) 
(list 960.5174 870.8008) 
(list 960.5174 870.8111) 
(list 960.5174 870.8214) 
(list 960.5174 870.8317) 
(list 960.5174 870.8419) 
(list 960.5174 870.8522) 
(list 960.5174 870.8625) 
(list 960.5174 870.8728) 
(list 960.5174 870.8831) 
(list 960.5174 870.8933) 
(list 960.5174 870.9036) 
(list 960.5174 870.9139) 
(list 960.5174 870.9242) 
(list 960.5174 870.9344) 
(list 960.5174 870.9447) 
(list 960.5174 870.955) 
(list 960.5174 870.9653) 
(list 960.5174 870.9756) 
(list 960.5174 870.9858) 
(list 960.5174 870.9961) 
(list 960.5174 871.0064) 
(list 960.5174 871.0167) 
(list 960.5174 871.0269) 
(list 960.5174 871.0372) 
(list 960.5174 871.0475) 
(list 960.5174 871.0578) 
(list 960.5174 871.0681) 
(list 960.5174 871.0783) 
(list 960.5174 871.0886) 
(list 960.5174 871.0989) 
(list 960.5174 871.1092) 
(list 960.5174 871.1194) 
(list 960.5174 871.1297) 
(list 960.5174 871.14) 
(list 961.086 871.14)))
(apply 'command (append '("pline") coords '("c")))
(setq tap3 (ssadd (entlast) tap3))
(command "_mirror" (entlast) "" "960,900" "960,901" "No")
(setq tap3 (ssadd (entlast) tap3))
(setq coords (list 
(list 960 871.14) 
(list 960.135 871.14) 
(list 960.135 871.1503) 
(list 960.135 871.1606) 
(list 960.135 871.1708) 
(list 960.135 871.1811) 
(list 960.135 871.1914) 
(list 960.135 871.2017) 
(list 960.135 871.2119) 
(list 960.135 871.2222) 
(list 960.135 871.2325) 
(list 960.135 871.2428) 
(list 960.135 871.2531) 
(list 960.135 871.2633) 
(list 960.135 871.2736) 
(list 960.135 871.2839) 
(list 960.135 871.2942) 
(list 960.135 871.3044) 
(list 960.135 871.3147) 
(list 960.135 871.325) 
(list 960.135 871.3353) 
(list 960.135 871.3456) 
(list 960.135 871.3558) 
(list 960.135 871.3661) 
(list 960.135 871.3764) 
(list 960.135 871.3867) 
(list 960.135 871.3969) 
(list 960.135 871.4072) 
(list 960.135 871.4175) 
(list 960.135 871.4278) 
(list 960.135 871.4381) 
(list 960.135 871.4483) 
(list 960.135 871.4586) 
(list 960.135 871.4689) 
(list 960.135 871.4792) 
(list 960.135 871.4894) 
(list 960.135 871.4997) 
(list 960.135 871.51) 
(list 960 871.51)))
(apply 'command (append '("pline") coords '("c")))
(setq tap3 (ssadd (entlast) tap3))
(command "_mirror" (entlast) "" "960,900" "960,901" "No")
(setq tap3 (ssadd (entlast) tap3))
(setq coords (list 
(list 960.5259 871.14) 
(list 960.5174 871.14) 
(list 960.516 871.1503) 
(list 960.5115 871.1606) 
(list 960.5039 871.1708) 
(list 960.4934 871.1811) 
(list 960.4804 871.1914) 
(list 960.4653 871.2017) 
(list 960.4485 871.2119) 
(list 960.4304 871.2222) 
(list 960.4117 871.2325) 
(list 960.393 871.2428) 
(list 960.3747 871.2531) 
(list 960.3574 871.2633) 
(list 960.3418 871.2736) 
(list 960.3282 871.2839) 
(list 960.3171 871.2942) 
(list 960.3088 871.3044) 
(list 960.3036 871.3147) 
(list 960.3017 871.325) 
(list 960.3031 871.3353) 
(list 960.3078 871.3456) 
(list 960.3157 871.3558) 
(list 960.3266 871.3661) 
(list 960.3401 871.3764) 
(list 960.3559 871.3867) 
(list 960.3734 871.3969) 
(list 960.3922 871.4072) 
(list 960.4116 871.4175) 
(list 960.4311 871.4278) 
(list 960.4501 871.4381) 
(list 960.468 871.4483) 
(list 960.4843 871.4586) 
(list 960.4984 871.4689) 
(list 960.51 871.4792) 
(list 960.5186 871.4894) 
(list 960.524 871.4997) 
(list 960.5259 871.51) 
(list 960.5259 871.51)))
(apply 'command (append '("pline") coords '("c")))
(setq tap3 (ssadd (entlast) tap3))
(command "_mirror" (entlast) "" "960,900" "960,901" "No")
(setq tap3 (ssadd (entlast) tap3))
(setq coords (list 
(list 961.086 871.14) 
(list 960.5259 871.14) 
(list 960.5259 871.1503) 
(list 960.5259 871.1606) 
(list 960.5259 871.1708) 
(list 960.5259 871.1811) 
(list 960.5259 871.1914) 
(list 960.5259 871.2017) 
(list 960.5259 871.2119) 
(list 960.5259 871.2222) 
(list 960.5259 871.2325) 
(list 960.5259 871.2428) 
(list 960.5259 871.2531) 
(list 960.5259 871.2633) 
(list 960.5259 871.2736) 
(list 960.5259 871.2839) 
(list 960.5259 871.2942) 
(list 960.5259 871.3044) 
(list 960.5259 871.3147) 
(list 960.5259 871.325) 
(list 960.5259 871.3353) 
(list 960.5259 871.3456) 
(list 960.5259 871.3558) 
(list 960.5259 871.3661) 
(list 960.5259 871.3764) 
(list 960.5259 871.3867) 
(list 960.5259 871.3969) 
(list 960.5259 871.4072) 
(list 960.5259 871.4175) 
(list 960.5259 871.4278) 
(list 960.5259 871.4381) 
(list 960.5259 871.4483) 
(list 960.5259 871.4586) 
(list 960.5259 871.4689) 
(list 960.5259 871.4792) 
(list 960.5259 871.4894) 
(list 960.5259 871.4997) 
(list 960.5259 871.51) 
(list 961.086 871.51)))
(apply 'command (append '("pline") coords '("c")))
(setq tap3 (ssadd (entlast) tap3))
(command "_mirror" (entlast) "" "960,900" "960,901" "No")
(setq tap3 (ssadd (entlast) tap3))
(setq coords (list 
(list 960 871.51) 
(list 960.135 871.51) 
(list 960.135 871.5203) 
(list 960.135 871.5306) 
(list 960.135 871.5408) 
(list 960.135 871.5511) 
(list 960.135 871.5614) 
(list 960.135 871.5717) 
(list 960.135 871.5819) 
(list 960.135 871.5922) 
(list 960.135 871.6025) 
(list 960.135 871.6128) 
(list 960.135 871.6231) 
(list 960.135 871.6333) 
(list 960.135 871.6436) 
(list 960.135 871.6539) 
(list 960.135 871.6642) 
(list 960.135 871.6744) 
(list 960.135 871.6847) 
(list 960.135 871.695) 
(list 960.135 871.7053) 
(list 960.135 871.7156) 
(list 960.135 871.7258) 
(list 960.135 871.7361) 
(list 960.135 871.7464) 
(list 960.135 871.7567) 
(list 960.135 871.7669) 
(list 960.135 871.7772) 
(list 960.135 871.7875) 
(list 960.135 871.7978) 
(list 960.135 871.8081) 
(list 960.135 871.8183) 
(list 960.135 871.8286) 
(list 960.135 871.8389) 
(list 960.135 871.8492) 
(list 960.135 871.8594) 
(list 960.135 871.8697) 
(list 960.135 871.88) 
(list 960 871.88)))
(apply 'command (append '("pline") coords '("c")))
(setq tap3 (ssadd (entlast) tap3))
(command "_mirror" (entlast) "" "960,900" "960,901" "No")
(setq tap3 (ssadd (entlast) tap3))
(setq coords (list 
(list 960.5345 871.51) 
(list 960.5259 871.51) 
(list 960.5244 871.5203) 
(list 960.5195 871.5306) 
(list 960.5112 871.5408) 
(list 960.4999 871.5511) 
(list 960.4858 871.5614) 
(list 960.4694 871.5717) 
(list 960.4512 871.5819) 
(list 960.4317 871.5922) 
(list 960.4115 871.6025) 
(list 960.3912 871.6128) 
(list 960.3714 871.6231) 
(list 960.3528 871.6333) 
(list 960.3359 871.6436) 
(list 960.3212 871.6539) 
(list 960.3092 871.6642) 
(list 960.3002 871.6744) 
(list 960.2947 871.6847) 
(list 960.2926 871.695) 
(list 960.2942 871.7053) 
(list 960.2993 871.7156) 
(list 960.3079 871.7258) 
(list 960.3196 871.7361) 
(list 960.3342 871.7464) 
(list 960.3512 871.7567) 
(list 960.3701 871.7669) 
(list 960.3904 871.7772) 
(list 960.4113 871.7875) 
(list 960.4324 871.7978) 
(list 960.4529 871.8081) 
(list 960.4722 871.8183) 
(list 960.4897 871.8286) 
(list 960.5049 871.8389) 
(list 960.5173 871.8492) 
(list 960.5266 871.8594) 
(list 960.5324 871.8697) 
(list 960.5345 871.88) 
(list 960.5345 871.88)))
(apply 'command (append '("pline") coords '("c")))
(setq tap3 (ssadd (entlast) tap3))
(command "_mirror" (entlast) "" "960,900" "960,901" "No")
(setq tap3 (ssadd (entlast) tap3))
(setq coords (list 
(list 961.086 871.51) 
(list 960.5345 871.51) 
(list 960.5345 871.5203) 
(list 960.5345 871.5306) 
(list 960.5345 871.5408) 
(list 960.5345 871.5511) 
(list 960.5345 871.5614) 
(list 960.5345 871.5717) 
(list 960.5345 871.5819) 
(list 960.5345 871.5922) 
(list 960.5345 871.6025) 
(list 960.5345 871.6128) 
(list 960.5345 871.6231) 
(list 960.5345 871.6333) 
(list 960.5345 871.6436) 
(list 960.5345 871.6539) 
(list 960.5345 871.6642) 
(list 960.5345 871.6744) 
(list 960.5345 871.6847) 
(list 960.5345 871.695) 
(list 960.5345 871.7053) 
(list 960.5345 871.7156) 
(list 960.5345 871.7258) 
(list 960.5345 871.7361) 
(list 960.5345 871.7464) 
(list 960.5345 871.7567) 
(list 960.5345 871.7669) 
(list 960.5345 871.7772) 
(list 960.5345 871.7875) 
(list 960.5345 871.7978) 
(list 960.5345 871.8081) 
(list 960.5345 871.8183) 
(list 960.5345 871.8286) 
(list 960.5345 871.8389) 
(list 960.5345 871.8492) 
(list 960.5345 871.8594) 
(list 960.5345 871.8697) 
(list 960.5345 871.88) 
(list 961.086 871.88)))
(apply 'command (append '("pline") coords '("c")))
(setq tap3 (ssadd (entlast) tap3))
(command "_mirror" (entlast) "" "960,900" "960,901" "No")
(setq tap3 (ssadd (entlast) tap3))
(setq coords (list 
(list 960 871.88) 
(list 960.135 871.88) 
(list 960.135 871.8903) 
(list 960.135 871.9006) 
(list 960.135 871.9108) 
(list 960.135 871.9211) 
(list 960.135 871.9314) 
(list 960.135 871.9417) 
(list 960.135 871.9519) 
(list 960.135 871.9622) 
(list 960.135 871.9725) 
(list 960.135 871.9828) 
(list 960.135 871.9931) 
(list 960.135 872.0033) 
(list 960.135 872.0136) 
(list 960.135 872.0239) 
(list 960.135 872.0342) 
(list 960.135 872.0444) 
(list 960.135 872.0547) 
(list 960.135 872.065) 
(list 960.135 872.0753) 
(list 960.135 872.0856) 
(list 960.135 872.0958) 
(list 960.135 872.1061) 
(list 960.135 872.1164) 
(list 960.135 872.1267) 
(list 960.135 872.1369) 
(list 960.135 872.1472) 
(list 960.135 872.1575) 
(list 960.135 872.1678) 
(list 960.135 872.1781) 
(list 960.135 872.1883) 
(list 960.135 872.1986) 
(list 960.135 872.2089) 
(list 960.135 872.2192) 
(list 960.135 872.2294) 
(list 960.135 872.2397) 
(list 960.135 872.25) 
(list 960 872.25)))
(apply 'command (append '("pline") coords '("c")))
(setq tap3 (ssadd (entlast) tap3))
(command "_mirror" (entlast) "" "960,900" "960,901" "No")
(setq tap3 (ssadd (entlast) tap3))
(setq coords (list 
(list 960.543 871.88) 
(list 960.5345 871.88) 
(list 960.5328 871.8903) 
(list 960.5275 871.9006) 
(list 960.5186 871.9108) 
(list 960.5064 871.9211) 
(list 960.4912 871.9314) 
(list 960.4736 871.9417) 
(list 960.4539 871.9519) 
(list 960.4329 871.9622) 
(list 960.4112 871.9725) 
(list 960.3894 871.9828) 
(list 960.3681 871.9931) 
(list 960.3481 872.0033) 
(list 960.3299 872.0136) 
(list 960.3142 872.0239) 
(list 960.3013 872.0342) 
(list 960.2917 872.0444) 
(list 960.2857 872.0547) 
(list 960.2835 872.065) 
(list 960.2852 872.0753) 
(list 960.2908 872.0856) 
(list 960.3 872.0958) 
(list 960.3126 872.1061) 
(list 960.3283 872.1164) 
(list 960.3466 872.1267) 
(list 960.3669 872.1369) 
(list 960.3886 872.1472) 
(list 960.4111 872.1575) 
(list 960.4336 872.1678) 
(list 960.4556 872.1781) 
(list 960.4763 872.1883) 
(list 960.4951 872.1986) 
(list 960.5114 872.2089) 
(list 960.5247 872.2192) 
(list 960.5346 872.2294) 
(list 960.5408 872.2397) 
(list 960.543 872.25) 
(list 960.543 872.25)))
(apply 'command (append '("pline") coords '("c")))
(setq tap3 (ssadd (entlast) tap3))
(command "_mirror" (entlast) "" "960,900" "960,901" "No")
(setq tap3 (ssadd (entlast) tap3))
(setq coords (list 
(list 961.086 871.88) 
(list 960.543 871.88) 
(list 960.543 871.8903) 
(list 960.543 871.9006) 
(list 960.543 871.9108) 
(list 960.543 871.9211) 
(list 960.543 871.9314) 
(list 960.543 871.9417) 
(list 960.543 871.9519) 
(list 960.543 871.9622) 
(list 960.543 871.9725) 
(list 960.543 871.9828) 
(list 960.543 871.9931) 
(list 960.543 872.0033) 
(list 960.543 872.0136) 
(list 960.543 872.0239) 
(list 960.543 872.0342) 
(list 960.543 872.0444) 
(list 960.543 872.0547) 
(list 960.543 872.065) 
(list 960.543 872.0753) 
(list 960.543 872.0856) 
(list 960.543 872.0958) 
(list 960.543 872.1061) 
(list 960.543 872.1164) 
(list 960.543 872.1267) 
(list 960.543 872.1369) 
(list 960.543 872.1472) 
(list 960.543 872.1575) 
(list 960.543 872.1678) 
(list 960.543 872.1781) 
(list 960.543 872.1883) 
(list 960.543 872.1986) 
(list 960.543 872.2089) 
(list 960.543 872.2192) 
(list 960.543 872.2294) 
(list 960.543 872.2397) 
(list 960.543 872.25) 
(list 961.086 872.25)))
(apply 'command (append '("pline") coords '("c")))
(setq tap3 (ssadd (entlast) tap3))
(command "_mirror" (entlast) "" "960,900" "960,901" "No")
(setq tap3 (ssadd (entlast) tap3))
(command "_block" "blktap3" "960,900" tap3 "")
(command "_insert" "blktap3" "960,900" "1" "1" "0")
(command "_insert" "blktap3" "960,900" "1" "1" "180")
(setq uc3 nil)
(setq uc3 (ssadd))
(setq coords (list 
(list 0 -0.185) 
(list 0.135 -0.185) 
(list 0.135 -0.17472) 
(list 0.135 -0.16444) 
(list 0.135 -0.15417) 
(list 0.135 -0.14389) 
(list 0.135 -0.13361) 
(list 0.135 -0.12333) 
(list 0.135 -0.11306) 
(list 0.135 -0.10278) 
(list 0.135 -0.0925) 
(list 0.135 -0.082222) 
(list 0.135 -0.071944) 
(list 0.135 -0.061667) 
(list 0.135 -0.051389) 
(list 0.135 -0.041111) 
(list 0.135 -0.030833) 
(list 0.135 -0.020556) 
(list 0.135 -0.010278) 
(list 0.135 0) 
(list 0.135 0.010278) 
(list 0.135 0.020556) 
(list 0.135 0.030833) 
(list 0.135 0.041111) 
(list 0.135 0.051389) 
(list 0.135 0.061667) 
(list 0.135 0.071944) 
(list 0.135 0.082222) 
(list 0.135 0.0925) 
(list 0.135 0.10278) 
(list 0.135 0.11306) 
(list 0.135 0.12333) 
(list 0.135 0.13361) 
(list 0.135 0.14389) 
(list 0.135 0.15417) 
(list 0.135 0.16444) 
(list 0.135 0.17472) 
(list 0.135 0.185) 
(list 0 0.185)))
(apply 'command (append '("pline") coords '("c")))
(setq uc3 (ssadd (entlast) uc3))
(setq coords (list 
(list 1.086 -0.185) 
(list 0.543 -0.185) 
(list 0.541 -0.17472) 
(list 0.53504 -0.16444) 
(list 0.52531 -0.15417) 
(list 0.51212 -0.14389) 
(list 0.49585 -0.13361) 
(list 0.477 -0.12333) 
(list 0.45615 -0.11306) 
(list 0.43392 -0.10278) 
(list 0.411 -0.0925) 
(list 0.38808 -0.082222) 
(list 0.36585 -0.071944) 
(list 0.345 -0.061667) 
(list 0.32615 -0.051389) 
(list 0.30988 -0.041111) 
(list 0.29668 -0.030833) 
(list 0.28696 -0.020556) 
(list 0.28101 -0.010278) 
(list 0.279 0) 
(list 0.28101 0.010278) 
(list 0.28696 0.020556) 
(list 0.29668 0.030833) 
(list 0.30988 0.041111) 
(list 0.32615 0.051389) 
(list 0.345 0.061667) 
(list 0.36585 0.071944) 
(list 0.38808 0.082222) 
(list 0.411 0.0925) 
(list 0.43392 0.10278) 
(list 0.45615 0.11306) 
(list 0.477 0.12333) 
(list 0.49585 0.13361) 
(list 0.51212 0.14389) 
(list 0.52531 0.15417) 
(list 0.53504 0.16444) 
(list 0.541 0.17472) 
(list 0.543 0.185) 
(list 1.086 0.185)))
(apply 'command (append '("pline") coords '("c")))
(setq uc3 (ssadd (entlast) uc3))
(command "_block" "blkuc3" "0,0.185" uc3 "")
(command "_insert" "blkuc3" "960,872.62" "1" "1" "0")
(command "_insert" "blkuc3" "960,872.25" "1" "1" "180")
(command "_insert" "blkuc3" "960,872.99" "1" "1" "0")
(command "_insert" "blkuc3" "960,872.62" "1" "1" "180")
(command "_insert" "blkuc3" "960,873.36" "1" "1" "0")
(command "_insert" "blkuc3" "960,872.99" "1" "1" "180")
(command "_insert" "blkuc3" "960,873.73" "1" "1" "0")
(command "_insert" "blkuc3" "960,873.36" "1" "1" "180")
(command "_insert" "blkuc3" "960,874.1" "1" "1" "0")
(command "_insert" "blkuc3" "960,873.73" "1" "1" "180")
(command "_insert" "blkuc3" "960,874.47" "1" "1" "0")
(command "_insert" "blkuc3" "960,874.1" "1" "1" "180")
(command "_insert" "blkuc3" "960,874.84" "1" "1" "0")
(command "_insert" "blkuc3" "960,874.47" "1" "1" "180")
(command "_insert" "blkuc3" "960,875.21" "1" "1" "0")
(command "_insert" "blkuc3" "960,874.84" "1" "1" "180")
(command "_insert" "blkuc3" "960,875.58" "1" "1" "0")
(command "_insert" "blkuc3" "960,875.21" "1" "1" "180")
(command "_insert" "blkuc3" "960,875.95" "1" "1" "0")
(command "_insert" "blkuc3" "960,875.58" "1" "1" "180")
(command "_insert" "blkuc3" "960,876.32" "1" "1" "0")
(command "_insert" "blkuc3" "960,875.95" "1" "1" "180")
(command "_insert" "blkuc3" "960,876.69" "1" "1" "0")
(command "_insert" "blkuc3" "960,876.32" "1" "1" "180")
(command "_insert" "blkuc3" "960,877.06" "1" "1" "0")
(command "_insert" "blkuc3" "960,876.69" "1" "1" "180")
(command "_insert" "blkuc3" "960,877.43" "1" "1" "0")
(command "_insert" "blkuc3" "960,877.06" "1" "1" "180")
(command "_insert" "blkuc3" "960,877.8" "1" "1" "0")
(command "_insert" "blkuc3" "960,877.43" "1" "1" "180")
(command "_insert" "blkuc3" "960,878.17" "1" "1" "0")
(command "_insert" "blkuc3" "960,877.8" "1" "1" "180")
(command "_insert" "blkuc3" "960,878.54" "1" "1" "0")
(command "_insert" "blkuc3" "960,878.17" "1" "1" "180")
(command "_insert" "blkuc3" "960,878.91" "1" "1" "0")
(command "_insert" "blkuc3" "960,878.54" "1" "1" "180")
(command "_insert" "blkuc3" "960,879.28" "1" "1" "0")
(command "_insert" "blkuc3" "960,878.91" "1" "1" "180")
(command "_insert" "blkuc3" "960,879.65" "1" "1" "0")
(command "_insert" "blkuc3" "960,879.28" "1" "1" "180")
(command "_insert" "blkuc3" "960,880.02" "1" "1" "0")
(command "_insert" "blkuc3" "960,879.65" "1" "1" "180")
(command "_insert" "blkuc3" "960,880.39" "1" "1" "0")
(command "_insert" "blkuc3" "960,880.02" "1" "1" "180")
(command "_insert" "blkuc3" "960,880.76" "1" "1" "0")
(command "_insert" "blkuc3" "960,880.39" "1" "1" "180")
(command "_insert" "blkuc3" "960,881.13" "1" "1" "0")
(command "_insert" "blkuc3" "960,880.76" "1" "1" "180")
(command "_insert" "blkuc3" "960,881.5" "1" "1" "0")
(command "_insert" "blkuc3" "960,881.13" "1" "1" "180")
(command "_insert" "blkuc3" "960,881.87" "1" "1" "0")
(command "_insert" "blkuc3" "960,881.5" "1" "1" "180")
(command "_insert" "blkuc3" "960,882.24" "1" "1" "0")
(command "_insert" "blkuc3" "960,881.87" "1" "1" "180")
(command "_insert" "blkuc3" "960,882.61" "1" "1" "0")
(command "_insert" "blkuc3" "960,882.24" "1" "1" "180")
(command "_insert" "blkuc3" "960,882.98" "1" "1" "0")
(command "_insert" "blkuc3" "960,882.61" "1" "1" "180")
(command "_insert" "blkuc3" "960,883.35" "1" "1" "0")
(command "_insert" "blkuc3" "960,882.98" "1" "1" "180")
(command "_insert" "blkuc3" "960,883.72" "1" "1" "0")
(command "_insert" "blkuc3" "960,883.35" "1" "1" "180")
(command "_insert" "blkuc3" "960,884.09" "1" "1" "0")
(command "_insert" "blkuc3" "960,883.72" "1" "1" "180")
(command "_insert" "blkuc3" "960,884.46" "1" "1" "0")
(command "_insert" "blkuc3" "960,884.09" "1" "1" "180")
(command "_insert" "blkuc3" "960,884.83" "1" "1" "0")
(command "_insert" "blkuc3" "960,884.46" "1" "1" "180")
(command "_insert" "blkuc3" "960,885.2" "1" "1" "0")
(command "_insert" "blkuc3" "960,884.83" "1" "1" "180")
(command "_insert" "blkuc3" "960,885.57" "1" "1" "0")
(command "_insert" "blkuc3" "960,885.2" "1" "1" "180")
(command "_insert" "blkuc3" "960,885.94" "1" "1" "0")
(command "_insert" "blkuc3" "960,885.57" "1" "1" "180")
(command "_insert" "blkuc3" "960,886.31" "1" "1" "0")
(command "_insert" "blkuc3" "960,885.94" "1" "1" "180")
(command "_insert" "blkuc3" "960,886.68" "1" "1" "0")
(command "_insert" "blkuc3" "960,886.31" "1" "1" "180")
(command "_insert" "blkuc3" "960,887.05" "1" "1" "0")
(command "_insert" "blkuc3" "960,886.68" "1" "1" "180")
(command "_insert" "blkuc3" "960,887.42" "1" "1" "0")
(command "_insert" "blkuc3" "960,887.05" "1" "1" "180")
(command "_insert" "blkuc3" "960,887.79" "1" "1" "0")
(command "_insert" "blkuc3" "960,887.42" "1" "1" "180")
(command "_insert" "blkuc3" "960,888.16" "1" "1" "0")
(command "_insert" "blkuc3" "960,887.79" "1" "1" "180")
(command "_insert" "blkuc3" "960,888.53" "1" "1" "0")
(command "_insert" "blkuc3" "960,888.16" "1" "1" "180")
(command "_insert" "blkuc3" "960,888.9" "1" "1" "0")
(command "_insert" "blkuc3" "960,888.53" "1" "1" "180")
(command "_insert" "blkuc3" "960,889.27" "1" "1" "0")
(command "_insert" "blkuc3" "960,888.9" "1" "1" "180")
(command "_insert" "blkuc3" "960,889.64" "1" "1" "0")
(command "_insert" "blkuc3" "960,889.27" "1" "1" "180")
(command "_insert" "blkuc3" "960,890.01" "1" "1" "0")
(command "_insert" "blkuc3" "960,889.64" "1" "1" "180")
(command "_insert" "blkuc3" "960,890.38" "1" "1" "0")
(command "_insert" "blkuc3" "960,890.01" "1" "1" "180")
(command "_insert" "blkuc3" "960,890.75" "1" "1" "0")
(command "_insert" "blkuc3" "960,890.38" "1" "1" "180")
(command "_insert" "blkuc3" "960,891.12" "1" "1" "0")
(command "_insert" "blkuc3" "960,890.75" "1" "1" "180")
(command "_insert" "blkuc3" "960,891.49" "1" "1" "0")
(command "_insert" "blkuc3" "960,891.12" "1" "1" "180")
(command "_insert" "blkuc3" "960,891.86" "1" "1" "0")
(command "_insert" "blkuc3" "960,891.49" "1" "1" "180")
(command "_insert" "blkuc3" "960,892.23" "1" "1" "0")
(command "_insert" "blkuc3" "960,891.86" "1" "1" "180")
(command "_insert" "blkuc3" "960,892.6" "1" "1" "0")
(command "_insert" "blkuc3" "960,892.23" "1" "1" "180")
(command "_insert" "blkuc3" "960,892.97" "1" "1" "0")
(command "_insert" "blkuc3" "960,892.6" "1" "1" "180")
(command "_insert" "blkuc3" "960,893.34" "1" "1" "0")
(command "_insert" "blkuc3" "960,892.97" "1" "1" "180")
(command "_insert" "blkuc3" "960,893.71" "1" "1" "0")
(command "_insert" "blkuc3" "960,893.34" "1" "1" "180")
(command "_insert" "blkuc3" "960,894.08" "1" "1" "0")
(command "_insert" "blkuc3" "960,893.71" "1" "1" "180")
(command "_insert" "blkuc3" "960,894.45" "1" "1" "0")
(command "_insert" "blkuc3" "960,894.08" "1" "1" "180")
(command "_insert" "blkuc3" "960,894.82" "1" "1" "0")
(command "_insert" "blkuc3" "960,894.45" "1" "1" "180")
(command "_insert" "blkuc3" "960,895.19" "1" "1" "0")
(command "_insert" "blkuc3" "960,894.82" "1" "1" "180")
(command "_insert" "blkuc3" "960,895.56" "1" "1" "0")
(command "_insert" "blkuc3" "960,895.19" "1" "1" "180")
(command "_insert" "blkuc3" "960,895.93" "1" "1" "0")
(command "_insert" "blkuc3" "960,895.56" "1" "1" "180")
(command "_insert" "blkuc3" "960,896.3" "1" "1" "0")
(command "_insert" "blkuc3" "960,895.93" "1" "1" "180")
(command "_insert" "blkuc3" "960,896.67" "1" "1" "0")
(command "_insert" "blkuc3" "960,896.3" "1" "1" "180")
(command "_insert" "blkuc3" "960,897.04" "1" "1" "0")
(command "_insert" "blkuc3" "960,896.67" "1" "1" "180")
(command "_insert" "blkuc3" "960,897.41" "1" "1" "0")
(command "_insert" "blkuc3" "960,897.04" "1" "1" "180")
(command "_insert" "blkuc3" "960,897.78" "1" "1" "0")
(command "_insert" "blkuc3" "960,897.41" "1" "1" "180")
(command "_insert" "blkuc3" "960,898.15" "1" "1" "0")
(command "_insert" "blkuc3" "960,897.78" "1" "1" "180")
(command "_insert" "blkuc3" "960,898.52" "1" "1" "0")
(command "_insert" "blkuc3" "960,898.15" "1" "1" "180")
(command "_insert" "blkuc3" "960,898.89" "1" "1" "0")
(command "_insert" "blkuc3" "960,898.52" "1" "1" "180")
(command "_insert" "blkuc3" "960,899.26" "1" "1" "0")
(command "_insert" "blkuc3" "960,898.89" "1" "1" "180")
(command "_insert" "blkuc3" "960,899.63" "1" "1" "0")
(command "_insert" "blkuc3" "960,899.26" "1" "1" "180")
(command "_insert" "blkuc3" "960,900" "1" "1" "0")
(command "_insert" "blkuc3" "960,899.63" "1" "1" "180")
(command "_insert" "blkuc3" "960,900.37" "1" "1" "0")
(command "_insert" "blkuc3" "960,900" "1" "1" "180")
(command "_insert" "blkuc3" "960,900.74" "1" "1" "0")
(command "_insert" "blkuc3" "960,900.37" "1" "1" "180")
(command "_insert" "blkuc3" "960,901.11" "1" "1" "0")
(command "_insert" "blkuc3" "960,900.74" "1" "1" "180")
(command "_insert" "blkuc3" "960,901.48" "1" "1" "0")
(command "_insert" "blkuc3" "960,901.11" "1" "1" "180")
(command "_insert" "blkuc3" "960,901.85" "1" "1" "0")
(command "_insert" "blkuc3" "960,901.48" "1" "1" "180")
(command "_insert" "blkuc3" "960,902.22" "1" "1" "0")
(command "_insert" "blkuc3" "960,901.85" "1" "1" "180")
(command "_insert" "blkuc3" "960,902.59" "1" "1" "0")
(command "_insert" "blkuc3" "960,902.22" "1" "1" "180")
(command "_insert" "blkuc3" "960,902.96" "1" "1" "0")
(command "_insert" "blkuc3" "960,902.59" "1" "1" "180")
(command "_insert" "blkuc3" "960,903.33" "1" "1" "0")
(command "_insert" "blkuc3" "960,902.96" "1" "1" "180")
(command "_insert" "blkuc3" "960,903.7" "1" "1" "0")
(command "_insert" "blkuc3" "960,903.33" "1" "1" "180")
(command "_insert" "blkuc3" "960,904.07" "1" "1" "0")
(command "_insert" "blkuc3" "960,903.7" "1" "1" "180")
(command "_insert" "blkuc3" "960,904.44" "1" "1" "0")
(command "_insert" "blkuc3" "960,904.07" "1" "1" "180")
(command "_insert" "blkuc3" "960,904.81" "1" "1" "0")
(command "_insert" "blkuc3" "960,904.44" "1" "1" "180")
(command "_insert" "blkuc3" "960,905.18" "1" "1" "0")
(command "_insert" "blkuc3" "960,904.81" "1" "1" "180")
(command "_insert" "blkuc3" "960,905.55" "1" "1" "0")
(command "_insert" "blkuc3" "960,905.18" "1" "1" "180")
(command "_insert" "blkuc3" "960,905.92" "1" "1" "0")
(command "_insert" "blkuc3" "960,905.55" "1" "1" "180")
(command "_insert" "blkuc3" "960,906.29" "1" "1" "0")
(command "_insert" "blkuc3" "960,905.92" "1" "1" "180")
(command "_insert" "blkuc3" "960,906.66" "1" "1" "0")
(command "_insert" "blkuc3" "960,906.29" "1" "1" "180")
(command "_insert" "blkuc3" "960,907.03" "1" "1" "0")
(command "_insert" "blkuc3" "960,906.66" "1" "1" "180")
(command "_insert" "blkuc3" "960,907.4" "1" "1" "0")
(command "_insert" "blkuc3" "960,907.03" "1" "1" "180")
(command "_insert" "blkuc3" "960,907.77" "1" "1" "0")
(command "_insert" "blkuc3" "960,907.4" "1" "1" "180")
(command "_insert" "blkuc3" "960,908.14" "1" "1" "0")
(command "_insert" "blkuc3" "960,907.77" "1" "1" "180")
(command "_insert" "blkuc3" "960,908.51" "1" "1" "0")
(command "_insert" "blkuc3" "960,908.14" "1" "1" "180")
(command "_insert" "blkuc3" "960,908.88" "1" "1" "0")
(command "_insert" "blkuc3" "960,908.51" "1" "1" "180")
(command "_insert" "blkuc3" "960,909.25" "1" "1" "0")
(command "_insert" "blkuc3" "960,908.88" "1" "1" "180")
(command "_insert" "blkuc3" "960,909.62" "1" "1" "0")
(command "_insert" "blkuc3" "960,909.25" "1" "1" "180")
(command "_insert" "blkuc3" "960,909.99" "1" "1" "0")
(command "_insert" "blkuc3" "960,909.62" "1" "1" "180")
(command "_insert" "blkuc3" "960,910.36" "1" "1" "0")
(command "_insert" "blkuc3" "960,909.99" "1" "1" "180")
(command "_insert" "blkuc3" "960,910.73" "1" "1" "0")
(command "_insert" "blkuc3" "960,910.36" "1" "1" "180")
(command "_insert" "blkuc3" "960,911.1" "1" "1" "0")
(command "_insert" "blkuc3" "960,910.73" "1" "1" "180")
(command "_insert" "blkuc3" "960,911.47" "1" "1" "0")
(command "_insert" "blkuc3" "960,911.1" "1" "1" "180")
(command "_insert" "blkuc3" "960,911.84" "1" "1" "0")
(command "_insert" "blkuc3" "960,911.47" "1" "1" "180")
(command "_insert" "blkuc3" "960,912.21" "1" "1" "0")
(command "_insert" "blkuc3" "960,911.84" "1" "1" "180")
(command "_insert" "blkuc3" "960,912.58" "1" "1" "0")
(command "_insert" "blkuc3" "960,912.21" "1" "1" "180")
(command "_insert" "blkuc3" "960,912.95" "1" "1" "0")
(command "_insert" "blkuc3" "960,912.58" "1" "1" "180")
(command "_insert" "blkuc3" "960,913.32" "1" "1" "0")
(command "_insert" "blkuc3" "960,912.95" "1" "1" "180")
(command "_insert" "blkuc3" "960,913.69" "1" "1" "0")
(command "_insert" "blkuc3" "960,913.32" "1" "1" "180")
(command "_insert" "blkuc3" "960,914.06" "1" "1" "0")
(command "_insert" "blkuc3" "960,913.69" "1" "1" "180")
(command "_insert" "blkuc3" "960,914.43" "1" "1" "0")
(command "_insert" "blkuc3" "960,914.06" "1" "1" "180")
(command "_insert" "blkuc3" "960,914.8" "1" "1" "0")
(command "_insert" "blkuc3" "960,914.43" "1" "1" "180")
(command "_insert" "blkuc3" "960,915.17" "1" "1" "0")
(command "_insert" "blkuc3" "960,914.8" "1" "1" "180")
(command "_insert" "blkuc3" "960,915.54" "1" "1" "0")
(command "_insert" "blkuc3" "960,915.17" "1" "1" "180")
(command "_insert" "blkuc3" "960,915.91" "1" "1" "0")
(command "_insert" "blkuc3" "960,915.54" "1" "1" "180")
(command "_insert" "blkuc3" "960,916.28" "1" "1" "0")
(command "_insert" "blkuc3" "960,915.91" "1" "1" "180")
(command "_insert" "blkuc3" "960,916.65" "1" "1" "0")
(command "_insert" "blkuc3" "960,916.28" "1" "1" "180")
(command "_insert" "blkuc3" "960,917.02" "1" "1" "0")
(command "_insert" "blkuc3" "960,916.65" "1" "1" "180")
(command "_insert" "blkuc3" "960,917.39" "1" "1" "0")
(command "_insert" "blkuc3" "960,917.02" "1" "1" "180")
(command "_insert" "blkuc3" "960,917.76" "1" "1" "0")
(command "_insert" "blkuc3" "960,917.39" "1" "1" "180")
(command "_insert" "blkuc3" "960,918.13" "1" "1" "0")
(command "_insert" "blkuc3" "960,917.76" "1" "1" "180")
(command "_insert" "blkuc3" "960,918.5" "1" "1" "0")
(command "_insert" "blkuc3" "960,918.13" "1" "1" "180")
(command "_insert" "blkuc3" "960,918.87" "1" "1" "0")
(command "_insert" "blkuc3" "960,918.5" "1" "1" "180")
(command "_insert" "blkuc3" "960,919.24" "1" "1" "0")
(command "_insert" "blkuc3" "960,918.87" "1" "1" "180")
(command "_insert" "blkuc3" "960,919.61" "1" "1" "0")
(command "_insert" "blkuc3" "960,919.24" "1" "1" "180")
(command "_insert" "blkuc3" "960,919.98" "1" "1" "0")
(command "_insert" "blkuc3" "960,919.61" "1" "1" "180")
(command "_insert" "blkuc3" "960,920.35" "1" "1" "0")
(command "_insert" "blkuc3" "960,919.98" "1" "1" "180")
(command "_insert" "blkuc3" "960,920.72" "1" "1" "0")
(command "_insert" "blkuc3" "960,920.35" "1" "1" "180")
(command "_insert" "blkuc3" "960,921.09" "1" "1" "0")
(command "_insert" "blkuc3" "960,920.72" "1" "1" "180")
(command "_insert" "blkuc3" "960,921.46" "1" "1" "0")
(command "_insert" "blkuc3" "960,921.09" "1" "1" "180")
(command "_insert" "blkuc3" "960,921.83" "1" "1" "0")
(command "_insert" "blkuc3" "960,921.46" "1" "1" "180")
(command "_insert" "blkuc3" "960,922.2" "1" "1" "0")
(command "_insert" "blkuc3" "960,921.83" "1" "1" "180")
(command "_insert" "blkuc3" "960,922.57" "1" "1" "0")
(command "_insert" "blkuc3" "960,922.2" "1" "1" "180")
(command "_insert" "blkuc3" "960,922.94" "1" "1" "0")
(command "_insert" "blkuc3" "960,922.57" "1" "1" "180")
(command "_insert" "blkuc3" "960,923.31" "1" "1" "0")
(command "_insert" "blkuc3" "960,922.94" "1" "1" "180")
(command "_insert" "blkuc3" "960,923.68" "1" "1" "0")
(command "_insert" "blkuc3" "960,923.31" "1" "1" "180")
(command "_insert" "blkuc3" "960,924.05" "1" "1" "0")
(command "_insert" "blkuc3" "960,923.68" "1" "1" "180")
(command "_insert" "blkuc3" "960,924.42" "1" "1" "0")
(command "_insert" "blkuc3" "960,924.05" "1" "1" "180")
(command "_insert" "blkuc3" "960,924.79" "1" "1" "0")
(command "_insert" "blkuc3" "960,924.42" "1" "1" "180")
(command "_insert" "blkuc3" "960,925.16" "1" "1" "0")
(command "_insert" "blkuc3" "960,924.79" "1" "1" "180")
(command "_insert" "blkuc3" "960,925.53" "1" "1" "0")
(command "_insert" "blkuc3" "960,925.16" "1" "1" "180")
(command "_insert" "blkuc3" "960,925.9" "1" "1" "0")
(command "_insert" "blkuc3" "960,925.53" "1" "1" "180")
(command "_insert" "blkuc3" "960,926.27" "1" "1" "0")
(command "_insert" "blkuc3" "960,925.9" "1" "1" "180")
(command "_insert" "blkuc3" "960,926.64" "1" "1" "0")
(command "_insert" "blkuc3" "960,926.27" "1" "1" "180")
(command "_insert" "blkuc3" "960,927.01" "1" "1" "0")
(command "_insert" "blkuc3" "960,926.64" "1" "1" "180")
(command "_insert" "blkuc3" "960,927.38" "1" "1" "0")
(command "_insert" "blkuc3" "960,927.01" "1" "1" "180")
(command "_insert" "blkuc3" "960,927.75" "1" "1" "0")
(command "_insert" "blkuc3" "960,927.38" "1" "1" "180")
(command "_layer" "set" "phccover" "")
(command "_rectangle" "958.914,933.3" "961.086,866.7")
(command "_layer" "set" "nitride" "")
(setq phc3 currobj)
(command "_layer" "set" "cover" "")
(command "_rectangle" "958.914,836.7" "961.086,963.3")
(command "_layer" "set" "nitride" "")
(command "_layer" "set" "text" "")
(command "_circle" "957.964,846.7" "0.075")
(command "_circle" "957.589,846.7" "0.15")
(command "_circle" "957.214,846.7" "0.075")
(command "_circle" "956.839,846.7" "0.15")
(command "_circle" "957.964,848.7" "0.075")
(command "_circle" "957.589,848.7" "0.075")
(command "_circle" "957.214,848.7" "0.15")
(command "_circle" "956.839,848.7" "0.15")
(command "_circle" "957.964,850.7" "0.075")
(command "_circle" "957.589,850.7" "0.15")
(command "_circle" "957.214,850.7" "0.15")
(command "_circle" "956.839,850.7" "0.15")
(command "_circle" "957.964,852.7" "0.075")
(command "_circle" "957.589,852.7" "0.075")
(command "_circle" "957.214,852.7" "0.075")
(command "_circle" "956.839,852.7" "0.075")
(command "_circle" "956.464,852.7" "0.15")
(command "_circle" "957.964,854.7" "0.075")
(command "_circle" "957.589,854.7" "0.15")
(command "_circle" "957.214,854.7" "0.075")
(command "_circle" "956.839,854.7" "0.075")
(command "_circle" "956.464,854.7" "0.15")
(command "_circle" "957.964,856.7" "0.075")
(command "_circle" "957.589,856.7" "0.075")
(command "_circle" "957.214,856.7" "0.15")
(command "_circle" "956.839,856.7" "0.075")
(command "_circle" "956.464,856.7" "0.15")
(command "_circle" "957.964,858.7" "0.075")
(command "_circle" "957.589,858.7" "0.15")
(command "_circle" "957.214,858.7" "0.15")
(command "_circle" "956.839,858.7" "0.075")
(command "_circle" "956.464,858.7" "0.15")
(command "_circle" "957.964,860.7" "0.075")
(command "_circle" "957.589,860.7" "0.075")
(command "_circle" "957.214,860.7" "0.075")
(command "_circle" "956.839,860.7" "0.15")
(command "_circle" "956.464,860.7" "0.15")
(command "_circle" "957.964,862.7" "0.075")
(command "_circle" "957.589,862.7" "0.15")
(command "_circle" "957.214,862.7" "0.075")
(command "_circle" "956.839,862.7" "0.15")
(command "_circle" "956.464,862.7" "0.15")
(command "_circle" "957.964,864.7" "0.075")
(command "_circle" "957.589,864.7" "0.075")
(command "_circle" "957.214,864.7" "0.15")
(command "_circle" "956.839,864.7" "0.15")
(command "_circle" "956.464,864.7" "0.15")
(command "_circle" "957.964,866.7" "0.075")
(command "_circle" "957.589,866.7" "0.15")
(command "_circle" "957.214,866.7" "0.15")
(command "_circle" "956.839,866.7" "0.15")
(command "_circle" "956.464,866.7" "0.15")
(command "_circle" "957.964,868.7" "0.075")
(command "_circle" "957.589,868.7" "0.075")
(command "_circle" "957.214,868.7" "0.075")
(command "_circle" "956.839,868.7" "0.075")
(command "_circle" "956.464,868.7" "0.075")
(command "_circle" "956.089,868.7" "0.15")
(command "_circle" "957.964,870.7" "0.075")
(command "_circle" "957.589,870.7" "0.15")
(command "_circle" "957.214,870.7" "0.075")
(command "_circle" "956.839,870.7" "0.075")
(command "_circle" "956.464,870.7" "0.075")
(command "_circle" "956.089,870.7" "0.15")
(command "_circle" "957.964,872.7" "0.075")
(command "_circle" "957.589,872.7" "0.075")
(command "_circle" "957.214,872.7" "0.15")
(command "_circle" "956.839,872.7" "0.075")
(command "_circle" "956.464,872.7" "0.075")
(command "_circle" "956.089,872.7" "0.15")
(command "_circle" "957.964,874.7" "0.075")
(command "_circle" "957.589,874.7" "0.15")
(command "_circle" "957.214,874.7" "0.15")
(command "_circle" "956.839,874.7" "0.075")
(command "_circle" "956.464,874.7" "0.075")
(command "_circle" "956.089,874.7" "0.15")
(command "_circle" "957.964,876.7" "0.075")
(command "_circle" "957.589,876.7" "0.075")
(command "_circle" "957.214,876.7" "0.075")
(command "_circle" "956.839,876.7" "0.15")
(command "_circle" "956.464,876.7" "0.075")
(command "_circle" "956.089,876.7" "0.15")
(command "_circle" "957.964,878.7" "0.075")
(command "_circle" "957.589,878.7" "0.15")
(command "_circle" "957.214,878.7" "0.075")
(command "_circle" "956.839,878.7" "0.15")
(command "_circle" "956.464,878.7" "0.075")
(command "_circle" "956.089,878.7" "0.15")
(command "_circle" "957.964,880.7" "0.075")
(command "_circle" "957.589,880.7" "0.075")
(command "_circle" "957.214,880.7" "0.15")
(command "_circle" "956.839,880.7" "0.15")
(command "_circle" "956.464,880.7" "0.075")
(command "_circle" "956.089,880.7" "0.15")
(command "_circle" "957.964,882.7" "0.075")
(command "_circle" "957.589,882.7" "0.15")
(command "_circle" "957.214,882.7" "0.15")
(command "_circle" "956.839,882.7" "0.15")
(command "_circle" "956.464,882.7" "0.075")
(command "_circle" "956.089,882.7" "0.15")
(command "_circle" "957.964,884.7" "0.075")
(command "_circle" "957.589,884.7" "0.075")
(command "_circle" "957.214,884.7" "0.075")
(command "_circle" "956.839,884.7" "0.075")
(command "_circle" "956.464,884.7" "0.15")
(command "_circle" "956.089,884.7" "0.15")
(command "_circle" "957.964,886.7" "0.075")
(command "_circle" "957.589,886.7" "0.15")
(command "_circle" "957.214,886.7" "0.075")
(command "_circle" "956.839,886.7" "0.075")
(command "_circle" "956.464,886.7" "0.15")
(command "_circle" "956.089,886.7" "0.15")
(command "_circle" "957.964,888.7" "0.075")
(command "_circle" "957.589,888.7" "0.075")
(command "_circle" "957.214,888.7" "0.15")
(command "_circle" "956.839,888.7" "0.075")
(command "_circle" "956.464,888.7" "0.15")
(command "_circle" "956.089,888.7" "0.15")
(command "_circle" "957.964,890.7" "0.075")
(command "_circle" "957.589,890.7" "0.15")
(command "_circle" "957.214,890.7" "0.15")
(command "_circle" "956.839,890.7" "0.075")
(command "_circle" "956.464,890.7" "0.15")
(command "_circle" "956.089,890.7" "0.15")
(command "_circle" "957.964,892.7" "0.075")
(command "_circle" "957.589,892.7" "0.075")
(command "_circle" "957.214,892.7" "0.075")
(command "_circle" "956.839,892.7" "0.15")
(command "_circle" "956.464,892.7" "0.15")
(command "_circle" "956.089,892.7" "0.15")
(command "_circle" "957.964,894.7" "0.075")
(command "_circle" "957.589,894.7" "0.15")
(command "_circle" "957.214,894.7" "0.075")
(command "_circle" "956.839,894.7" "0.15")
(command "_circle" "956.464,894.7" "0.15")
(command "_circle" "956.089,894.7" "0.15")
(command "_circle" "957.964,896.7" "0.075")
(command "_circle" "957.589,896.7" "0.075")
(command "_circle" "957.214,896.7" "0.15")
(command "_circle" "956.839,896.7" "0.15")
(command "_circle" "956.464,896.7" "0.15")
(command "_circle" "956.089,896.7" "0.15")
(command "_circle" "957.964,898.7" "0.075")
(command "_circle" "957.589,898.7" "0.15")
(command "_circle" "957.214,898.7" "0.15")
(command "_circle" "956.839,898.7" "0.15")
(command "_circle" "956.464,898.7" "0.15")
(command "_circle" "956.089,898.7" "0.15")
(command "_circle" "957.964,900.7" "0.075")
(command "_circle" "957.589,900.7" "0.075")
(command "_circle" "957.214,900.7" "0.075")
(command "_circle" "956.839,900.7" "0.075")
(command "_circle" "956.464,900.7" "0.075")
(command "_circle" "956.089,900.7" "0.075")
(command "_circle" "955.714,900.7" "0.15")
(command "_circle" "957.964,902.7" "0.075")
(command "_circle" "957.589,902.7" "0.15")
(command "_circle" "957.214,902.7" "0.075")
(command "_circle" "956.839,902.7" "0.075")
(command "_circle" "956.464,902.7" "0.075")
(command "_circle" "956.089,902.7" "0.075")
(command "_circle" "955.714,902.7" "0.15")
(command "_circle" "957.964,904.7" "0.075")
(command "_circle" "957.589,904.7" "0.075")
(command "_circle" "957.214,904.7" "0.15")
(command "_circle" "956.839,904.7" "0.075")
(command "_circle" "956.464,904.7" "0.075")
(command "_circle" "956.089,904.7" "0.075")
(command "_circle" "955.714,904.7" "0.15")
(command "_circle" "957.964,906.7" "0.075")
(command "_circle" "957.589,906.7" "0.15")
(command "_circle" "957.214,906.7" "0.15")
(command "_circle" "956.839,906.7" "0.075")
(command "_circle" "956.464,906.7" "0.075")
(command "_circle" "956.089,906.7" "0.075")
(command "_circle" "955.714,906.7" "0.15")
(command "_circle" "957.964,908.7" "0.075")
(command "_circle" "957.589,908.7" "0.075")
(command "_circle" "957.214,908.7" "0.075")
(command "_circle" "956.839,908.7" "0.15")
(command "_circle" "956.464,908.7" "0.075")
(command "_circle" "956.089,908.7" "0.075")
(command "_circle" "955.714,908.7" "0.15")
(command "_circle" "957.964,910.7" "0.075")
(command "_circle" "957.589,910.7" "0.15")
(command "_circle" "957.214,910.7" "0.075")
(command "_circle" "956.839,910.7" "0.15")
(command "_circle" "956.464,910.7" "0.075")
(command "_circle" "956.089,910.7" "0.075")
(command "_circle" "955.714,910.7" "0.15")
(command "_circle" "957.964,912.7" "0.075")
(command "_circle" "957.589,912.7" "0.075")
(command "_circle" "957.214,912.7" "0.15")
(command "_circle" "956.839,912.7" "0.15")
(command "_circle" "956.464,912.7" "0.075")
(command "_circle" "956.089,912.7" "0.075")
(command "_circle" "955.714,912.7" "0.15")
(command "_circle" "957.964,914.7" "0.075")
(command "_circle" "957.589,914.7" "0.15")
(command "_circle" "957.214,914.7" "0.15")
(command "_circle" "956.839,914.7" "0.15")
(command "_circle" "956.464,914.7" "0.075")
(command "_circle" "956.089,914.7" "0.075")
(command "_circle" "955.714,914.7" "0.15")
(command "_circle" "957.964,916.7" "0.075")
(command "_circle" "957.589,916.7" "0.075")
(command "_circle" "957.214,916.7" "0.075")
(command "_circle" "956.839,916.7" "0.075")
(command "_circle" "956.464,916.7" "0.15")
(command "_circle" "956.089,916.7" "0.075")
(command "_circle" "955.714,916.7" "0.15")
(command "_circle" "957.964,918.7" "0.075")
(command "_circle" "957.589,918.7" "0.15")
(command "_circle" "957.214,918.7" "0.075")
(command "_circle" "956.839,918.7" "0.075")
(command "_circle" "956.464,918.7" "0.15")
(command "_circle" "956.089,918.7" "0.075")
(command "_circle" "955.714,918.7" "0.15")
(command "_circle" "957.964,920.7" "0.075")
(command "_circle" "957.589,920.7" "0.075")
(command "_circle" "957.214,920.7" "0.15")
(command "_circle" "956.839,920.7" "0.075")
(command "_circle" "956.464,920.7" "0.15")
(command "_circle" "956.089,920.7" "0.075")
(command "_circle" "955.714,920.7" "0.15")
(command "_circle" "957.964,922.7" "0.075")
(command "_circle" "957.589,922.7" "0.15")
(command "_circle" "957.214,922.7" "0.15")
(command "_circle" "956.839,922.7" "0.075")
(command "_circle" "956.464,922.7" "0.15")
(command "_circle" "956.089,922.7" "0.075")
(command "_circle" "955.714,922.7" "0.15")
(command "_circle" "957.964,924.7" "0.075")
(command "_circle" "957.589,924.7" "0.075")
(command "_circle" "957.214,924.7" "0.075")
(command "_circle" "956.839,924.7" "0.15")
(command "_circle" "956.464,924.7" "0.15")
(command "_circle" "956.089,924.7" "0.075")
(command "_circle" "955.714,924.7" "0.15")
(command "_circle" "957.964,926.7" "0.075")
(command "_circle" "957.589,926.7" "0.15")
(command "_circle" "957.214,926.7" "0.075")
(command "_circle" "956.839,926.7" "0.15")
(command "_circle" "956.464,926.7" "0.15")
(command "_circle" "956.089,926.7" "0.075")
(command "_circle" "955.714,926.7" "0.15")
(command "_circle" "957.964,928.7" "0.075")
(command "_circle" "957.589,928.7" "0.075")
(command "_circle" "957.214,928.7" "0.15")
(command "_circle" "956.839,928.7" "0.15")
(command "_circle" "956.464,928.7" "0.15")
(command "_circle" "956.089,928.7" "0.075")
(command "_circle" "955.714,928.7" "0.15")
(command "_circle" "957.964,930.7" "0.075")
(command "_circle" "957.589,930.7" "0.15")
(command "_circle" "957.214,930.7" "0.15")
(command "_circle" "956.839,930.7" "0.15")
(command "_circle" "956.464,930.7" "0.15")
(command "_circle" "956.089,930.7" "0.075")
(command "_circle" "955.714,930.7" "0.15")
(command "_circle" "957.964,932.7" "0.075")
(command "_circle" "957.589,932.7" "0.075")
(command "_circle" "957.214,932.7" "0.075")
(command "_circle" "956.839,932.7" "0.075")
(command "_circle" "956.464,932.7" "0.075")
(command "_circle" "956.089,932.7" "0.15")
(command "_circle" "955.714,932.7" "0.15")
(command "_circle" "957.964,934.7" "0.075")
(command "_circle" "957.589,934.7" "0.15")
(command "_circle" "957.214,934.7" "0.075")
(command "_circle" "956.839,934.7" "0.075")
(command "_circle" "956.464,934.7" "0.075")
(command "_circle" "956.089,934.7" "0.15")
(command "_circle" "955.714,934.7" "0.15")
(command "_circle" "957.964,936.7" "0.075")
(command "_circle" "957.589,936.7" "0.075")
(command "_circle" "957.214,936.7" "0.15")
(command "_circle" "956.839,936.7" "0.075")
(command "_circle" "956.464,936.7" "0.075")
(command "_circle" "956.089,936.7" "0.15")
(command "_circle" "955.714,936.7" "0.15")
(command "_circle" "957.964,938.7" "0.075")
(command "_circle" "957.589,938.7" "0.15")
(command "_circle" "957.214,938.7" "0.15")
(command "_circle" "956.839,938.7" "0.075")
(command "_circle" "956.464,938.7" "0.075")
(command "_circle" "956.089,938.7" "0.15")
(command "_circle" "955.714,938.7" "0.15")
(command "_circle" "957.964,940.7" "0.075")
(command "_circle" "957.589,940.7" "0.075")
(command "_circle" "957.214,940.7" "0.075")
(command "_circle" "956.839,940.7" "0.15")
(command "_circle" "956.464,940.7" "0.075")
(command "_circle" "956.089,940.7" "0.15")
(command "_circle" "955.714,940.7" "0.15")
(command "_circle" "957.964,942.7" "0.075")
(command "_circle" "957.589,942.7" "0.15")
(command "_circle" "957.214,942.7" "0.075")
(command "_circle" "956.839,942.7" "0.15")
(command "_circle" "956.464,942.7" "0.075")
(command "_circle" "956.089,942.7" "0.15")
(command "_circle" "955.714,942.7" "0.15")
(command "_circle" "957.964,944.7" "0.075")
(command "_circle" "957.589,944.7" "0.075")
(command "_circle" "957.214,944.7" "0.15")
(command "_circle" "956.839,944.7" "0.15")
(command "_circle" "956.464,944.7" "0.075")
(command "_circle" "956.089,944.7" "0.15")
(command "_circle" "955.714,944.7" "0.15")
(command "_circle" "957.964,946.7" "0.075")
(command "_circle" "957.589,946.7" "0.15")
(command "_circle" "957.214,946.7" "0.15")
(command "_circle" "956.839,946.7" "0.15")
(command "_circle" "956.464,946.7" "0.075")
(command "_circle" "956.089,946.7" "0.15")
(command "_circle" "955.714,946.7" "0.15")
(command "_circle" "957.964,948.7" "0.075")
(command "_circle" "957.589,948.7" "0.075")
(command "_circle" "957.214,948.7" "0.075")
(command "_circle" "956.839,948.7" "0.075")
(command "_circle" "956.464,948.7" "0.15")
(command "_circle" "956.089,948.7" "0.15")
(command "_circle" "955.714,948.7" "0.15")
(command "_circle" "957.964,950.7" "0.075")
(command "_circle" "957.589,950.7" "0.15")
(command "_circle" "957.214,950.7" "0.075")
(command "_circle" "956.839,950.7" "0.075")
(command "_circle" "956.464,950.7" "0.15")
(command "_circle" "956.089,950.7" "0.15")
(command "_circle" "955.714,950.7" "0.15")
(command "_circle" "957.964,952.7" "0.075")
(command "_circle" "957.589,952.7" "0.075")
(command "_circle" "957.214,952.7" "0.15")
(command "_circle" "956.839,952.7" "0.075")
(command "_circle" "956.464,952.7" "0.15")
(command "_circle" "956.089,952.7" "0.15")
(command "_circle" "955.714,952.7" "0.15")
(command "_circle" "957.964,954.7" "0.075")
(command "_circle" "957.589,954.7" "0.15")
(command "_circle" "957.214,954.7" "0.15")
(command "_circle" "956.839,954.7" "0.075")
(command "_circle" "956.464,954.7" "0.15")
(command "_circle" "956.089,954.7" "0.15")
(command "_circle" "955.714,954.7" "0.15")
(command "_circle" "957.964,956.7" "0.075")
(command "_circle" "957.589,956.7" "0.075")
(command "_circle" "957.214,956.7" "0.075")
(command "_circle" "956.839,956.7" "0.15")
(command "_circle" "956.464,956.7" "0.15")
(command "_circle" "956.089,956.7" "0.15")
(command "_circle" "955.714,956.7" "0.15")
(command "_circle" "957.964,958.7" "0.075")
(command "_circle" "957.589,958.7" "0.15")
(command "_circle" "957.214,958.7" "0.075")
(command "_circle" "956.839,958.7" "0.15")
(command "_circle" "956.464,958.7" "0.15")
(command "_circle" "956.089,958.7" "0.15")
(command "_circle" "955.714,958.7" "0.15")
(command "_circle" "957.964,960.7" "0.075")
(command "_circle" "957.589,960.7" "0.075")
(command "_circle" "957.214,960.7" "0.15")
(command "_circle" "956.839,960.7" "0.15")
(command "_circle" "956.464,960.7" "0.15")
(command "_circle" "956.089,960.7" "0.15")
(command "_circle" "955.714,960.7" "0.15")
(command "_circle" "957.964,962.7" "0.075")
(command "_circle" "957.589,962.7" "0.15")
(command "_circle" "957.214,962.7" "0.15")
(command "_circle" "956.839,962.7" "0.15")
(command "_circle" "956.464,962.7" "0.15")
(command "_circle" "956.089,962.7" "0.15")
(command "_circle" "955.714,962.7" "0.15")
(command "_layer" "set" "nitride" "")
(command "_layer" "set" "text" "")
(command-s "_text" "946.914,963.3" "2" "-90" "a = 370 nm" )
(sssetfirst nil (ssget "_L"))
(if (not (numberp (vl-string-search "Mac" (getvar "platform")))) (c:txtexp))
(command "_layer" "set" "nitride" "")
(command "_layer" "set" "text" "")
(command-s "_text" "943.914,963.3" "2" "-90" "gap = 270 nm" )
(sssetfirst nil (ssget "_L"))
(if (not (numberp (vl-string-search "Mac" (getvar "platform")))) (c:txtexp))
(command "_layer" "set" "nitride" "")
(command "_layer" "set" "text" "")
(command-s "_text" "940.914,963.3" "2" "-90" "amplitude = 132 nm" )
(sssetfirst nil (ssget "_L"))
(if (not (numberp (vl-string-search "Mac" (getvar "platform")))) (c:txtexp))
(command "_layer" "set" "nitride" "")
(command "_layer" "set" "text" "")
(command-s "_text" "937.914,963.3" "2" "-90" "start width = 280 nm" )
(sssetfirst nil (ssget "_L"))
(if (not (numberp (vl-string-search "Mac" (getvar "platform")))) (c:txtexp))
(command "_layer" "set" "nitride" "")
(command "_layer" "set" "text" "")
(command-s "_text" "934.914,963.3" "2" "-90" "width = 276 nm" )
(sssetfirst nil (ssget "_L"))
(if (not (numberp (vl-string-search "Mac" (getvar "platform")))) (c:txtexp))
(command "_layer" "set" "nitride" "")
(command "_layer" "set" "text" "")
(command-s "_text" "931.914,963.3" "2" "-90" "taper: 15" )
(sssetfirst nil (ssget "_L"))
(if (not (numberp (vl-string-search "Mac" (getvar "platform")))) (c:txtexp))
(command "_layer" "set" "nitride" "")
(command "_layer" "set" "text" "")
(command-s "_text" "928.914,963.3" "2" "-90" "nominal: 150" )
(sssetfirst nil (ssget "_L"))
(if (not (numberp (vl-string-search "Mac" (getvar "platform")))) (c:txtexp))
(command "_layer" "set" "nitride" "")
(command "_layer" "set" "indicators" "")
(setq coords (list 
(list 880.415 940) 
(list 880.415 920) 
(list 860.415 900) 
(list 880.415 880) 
(list 880.415 860) 
(list 880.415 900) 
(list 880.415 887.0711) 
(list 867.4861 900) 
(list 880.415 912.9289) 
(list 880.415 900)))
(apply 'command (append '("pline") coords '("c")))
(command "._fillet" "radius" "1" "._fillet" "P" (entlast))
(setq coords (list 
(list 1039.585 940) 
(list 1039.585 920) 
(list 1059.585 900) 
(list 1039.585 880) 
(list 1039.585 860) 
(list 1039.585 900) 
(list 1039.585 887.0711) 
(list 1052.5139 900) 
(list 1039.585 912.9289) 
(list 1039.585 900)))
(apply 'command (append '("pline") coords '("c")))
(command "._fillet" "radius" "1" "._fillet" "P" (entlast))
(command "_layer" "set" "holes" "")
(command "_circle" "878.0629,914.1124" "0.5")
(command "_circle" "875.7109,911.7603" "0.5")
(command "_circle" "873.3588,909.4083" "0.5")
(command "_circle" "871.0067,907.0562" "0.5")
(command "_circle" "868.6547,904.7041" "0.5")
(command "_circle" "866.3026,902.3521" "0.5")
(command "_circle" "863.9505,900" "0.5")
(command "_circle" "866.3026,897.6479" "0.5")
(command "_circle" "868.6547,895.2959" "0.5")
(command "_circle" "871.0067,892.9438" "0.5")
(command "_circle" "873.3588,890.5917" "0.5")
(command "_circle" "875.7109,888.2397" "0.5")
(command "_circle" "878.0629,885.8876" "0.5")
(command "_circle" "1041.9371,914.1124" "0.5")
(command "_circle" "1044.2891,911.7603" "0.5")
(command "_circle" "1046.6412,909.4083" "0.5")
(command "_circle" "1048.9933,907.0562" "0.5")
(command "_circle" "1051.3453,904.7041" "0.5")
(command "_circle" "1053.6974,902.3521" "0.5")
(command "_circle" "1056.0495,900" "0.5")
(command "_circle" "1053.6974,897.6479" "0.5")
(command "_circle" "1051.3453,895.2959" "0.5")
(command "_circle" "1048.9933,892.9438" "0.5")
(command "_circle" "1046.6412,890.5917" "0.5")
(command "_circle" "1044.2891,888.2397" "0.5")
(command "_circle" "1041.9371,885.8876" "0.5")
(command "_layer" "set" "nitride" "")
(command "_block" "blkcoupler3" "960,900" coupler3 "")
(command "_insert" "blkcoupler3" "960,900" "1" "1" "0")
(command "_insert" "blkcoupler3" "960,900" "1" "1" "180")
(command "_block" "blksinglenanobeam3" "960,900" singlenanobeam3 "")
(command "_insert" "blksinglenanobeam3" "960,900" "1" "1" "0")
(command "_insert" "blksinglenanobeam3" "960,900" "1" "1" "180")
(command "_block" "blkanglednodearray3" "960,900" anglednodearray3 "")
(command "_insert" "blkanglednodearray3" "960,900" "1" "1" "0")
(command "_insert" "blkanglednodearray3" "960,900" "1" "1" "180")
(command "_block" "blkcooledsinglenanobeam3" "960,900" cooledsinglenanobeam3 "")
(command "_insert" "blkcooledsinglenanobeam3" "960,900" "1" "1" "0")
(command "_insert" "blkcooledsinglenanobeam3" "960,900" "1" "1" "180")
(command "_block" "blkyjunction3" "960,900" yjunction3 "")
(command "_insert" "blkyjunction3" "960,900" "1" "1" "0")
(command "_insert" "blkyjunction3" "960,900" "1" "1" "180")
; DRAWING BULGING VEE GROOVE
(command "_layer" "set" "vgroove" "")
(setq coords (list 
(list 885.415 -605) 
(list 885.415 0) 
(list 885.415 0) 
(list 885.415 1800) 
(list 885.415 1800) 
(list 885.415 2405) 
(list 1034.585 2405) 
(list 1034.585 1800) 
(list 1034.585 1800) 
(list 1034.585 0) 
(list 1034.585 0) 
(list 1034.585 -605)))
(apply 'command (append '("pline") coords '("c")))
(command "._fillet" "radius" "0" "._fillet" "P" (entlast))
(command "_layer" "set" "window" "")
(command "_rectangle" "885.415,-1935" "1034.585,-600")
(command "_rectangle" "885.415,2400" "1034.585,5300")
(command "_layer" "set" "grid" "")
(command "_rectangle" "886.415,-1934" "909.9433,-1909.2133")
(command "_array" "last" "" "R" "75" "3" "25.7867" "24.5283")
(command "_rectangle" "961,-1934" "984.5283,-1909.2133")
(command "_array" "last" "" "R" "75" "3" "25.7867" "24.5283")
(command "_rectangle" "886.415,1" "909.9433,25.7")
(command "_array" "last" "" "R" "70" "3" "25.7" "24.5283")
(command "_rectangle" "961,1" "984.5283,25.7")
(command "_array" "last" "" "R" "70" "3" "25.7" "24.5283")
(command "_rectangle" "886.415,1801" "909.9433,1825.9185")
(command "_array" "last" "" "R" "135" "3" "25.9185" "24.5283")
(command "_rectangle" "961,1801" "984.5283,1825.9185")
(command "_array" "last" "" "R" "135" "3" "25.9185" "24.5283")
(command "_layer" "set" "vgrooveFDA" "")
(command "_rectangle" "1034.585,-2233" "885.415,-1933")
(command "_layer" "set" "nitride" "")
(command "_layer" "set" "holes" "")
(command "_circle" "1037.085,331.5" "0.5")
(command "_array" "last" "" "R" "379" "1" "3" "2.5")
(command "_circle" "882.915,331.5" "0.5")
(command "_array" "last" "" "R" "379" "1" "3" "-2.5")
(command "_layer" "set" "nitride" "")
(command "_layer" "set" "window" "")
(command "_layer" "set" "window" "")
(command "_rectangle" "1039.585,0" "1200.415,1800")
(command "._fillet" "radius" "20" "._fillet" "P" (entlast))
(command "_layer" "set" "grid" "")
(command "_rectangle" "1040.585,1" "1062.4179,25.7")
(command "_array" "last" "" "R" "70" "7" "25.7" "22.8329")
(command "_layer" "set" "nitride" "")
; DRAWING REGION LAYER
(command "_layer" "set" "regionLayer3" "")
(command "_rectangle" "880,-460" "1040,2260")
(command "_layer" "set" "nitride" "")
(setq coupler3 nil)
(setq singlenanobeam3 nil)
(setq anglednodearray3 nil)
(setq cooledsinglenanobeam3 nil)
(setq yjunction3 nil)
; DEVICE #4
(command "_layer" "set" "window" "")
(command "_circle" "1192.915,-415" "5")
(command "_circle" "1192.915,-402.5" "5")
(command "_circle" "1192.915,-390" "5")
(command "_circle" "1192.915,-377.5" "5")
(command "_layer" "set" "nitride" "")
(setq currobj nil)
(setq currobj (ssadd))
; DRAWING COUPLER
(setq coords (list 
(list 1280.0575 -415) 
(list 1280.0575 -413) 
(list 1353.585 -413) 
(list 1353.585 -413) 
(list 1353.9677 -413.0761) 
(list 1354.2921 -413.2929) 
(list 1354.5089 -413.6173) 
(list 1354.585 -414) 
(list 1354.585 -411.8) 
(list 1354.585 -411.8) 
(list 1354.5089 -412.1827) 
(list 1354.2921 -412.5071) 
(list 1353.9677 -412.7239) 
(list 1353.585 -412.8) 
(list 1280.0575 -412.8) 
(list 1280.0575 -410.8) 
(list 1279.9425 -410.8) 
(list 1279.9425 -412.8) 
(list 1206.415 -412.8) 
(list 1206.0323 -412.7239) 
(list 1205.7079 -412.5071) 
(list 1205.4911 -412.1827) 
(list 1205.415 -411.8) 
(list 1205.415 -411.8) 
(list 1205.415 -414) 
(list 1205.4911 -413.6173) 
(list 1205.7079 -413.2929) 
(list 1206.0323 -413.0761) 
(list 1206.415 -413) 
(list 1206.415 -413) 
(list 1279.9425 -413) 
(list 1279.9425 -415)))
(apply 'command (append '("pline") coords '("c")))
(setq currobj (ssadd (entlast) currobj))
(command "._fillet" "radius" "0.3" "._fillet" "P" (entlast))
(command "_layer" "set" "holes" "")
(command "_circle" "1280,-412.9" "0.113")
(setq currobj (ssadd (entlast) currobj))
(command "_layer" "set" "nitride" "")
(command "_layer" "set" "text" "")
(command "_circle" "1279.2,-415" "0.075")
(command "_circle" "1279.2,-414.7" "0.075")
(command "_circle" "1279.2,-414.4" "0.075")
(command "_circle" "1278.9,-415" "0.075")
(command "_circle" "1278.9,-414.7" "0.075")
(command "_circle" "1278.9,-414.4" "0.075")
(command "_circle" "1278.6,-415" "0.075")
(command "_circle" "1278.6,-414.7" "0.075")
(command "_circle" "1278.6,-414.4" "0.075")
(command "_layer" "set" "nitride" "")
(command "_layer" "set" "prebias" "")
(command "_rectangle" "1205.415,-414" "1354.585,-411.8")
(setq currobj (ssadd (entlast) currobj))
(command "_rectangle" "1279.9425,-415" "1280.0575,-410.8")
(setq currobj (ssadd (entlast) currobj))
(command "_layer" "set" "nitride" "")
(setq coupler4 currobj)
(setq currobj nil)
(setq currobj (ssadd))
; DRAWING SINGLE NANOBEAM
(setq coords (list 
(list 1280.0575 -410.8) 
(list 1280.0575 -409.1417) 
(list 1280.0575 -407.4833) 
(list 1280.0575 -405.825) 
(list 1280.0575 -404.1667) 
(list 1280.0575 -402.5083) 
(list 1280.0575 -400.85) 
(list 1280.0575 -399.1917) 
(list 1280.0575 -397.5333) 
(list 1280.0576 -395.875) 
(list 1280.0576 -394.2167) 
(list 1280.0576 -392.5583) 
(list 1280.0576 -390.9) 
(list 1280.0577 -389.2417) 
(list 1280.0577 -387.5833) 
(list 1280.0577 -385.925) 
(list 1280.0578 -384.2667) 
(list 1280.0579 -382.6083) 
(list 1280.0579 -380.95) 
(list 1280.058 -379.2917) 
(list 1280.0581 -377.6333) 
(list 1280.0582 -375.975) 
(list 1280.0583 -374.3167) 
(list 1280.0584 -372.6583) 
(list 1280.0585 -371) 
(list 1280.0587 -369.3417) 
(list 1280.0588 -367.6833) 
(list 1280.059 -366.025) 
(list 1280.0591 -364.3667) 
(list 1280.0593 -362.7083) 
(list 1280.0595 -361.05) 
(list 1280.0597 -359.3917) 
(list 1280.0599 -357.7333) 
(list 1280.0602 -356.075) 
(list 1280.0604 -354.4167) 
(list 1280.0607 -352.7583) 
(list 1280.0609 -351.1) 
(list 1280.0612 -349.4417) 
(list 1280.0615 -347.7833) 
(list 1280.0619 -346.125) 
(list 1280.0622 -344.4667) 
(list 1280.0626 -342.8083) 
(list 1280.063 -341.15) 
(list 1280.0634 -339.4917) 
(list 1280.0638 -337.8333) 
(list 1280.0642 -336.175) 
(list 1280.0647 -334.5167) 
(list 1280.0652 -332.8583) 
(list 1280.0657 -331.2) 
(list 1280.0662 -329.5417) 
(list 1280.0667 -327.8833) 
(list 1280.0673 -326.225) 
(list 1280.0679 -324.5667) 
(list 1280.0685 -322.9083) 
(list 1280.0691 -321.25) 
(list 1280.0698 -319.5917) 
(list 1280.0705 -317.9333) 
(list 1280.0712 -316.275) 
(list 1280.0719 -314.6167) 
(list 1280.0727 -312.9583) 
(list 1280.0734 -311.3) 
(list 1280.0742 -309.6417) 
(list 1280.0751 -307.9833) 
(list 1280.0759 -306.325) 
(list 1280.0768 -304.6667) 
(list 1280.0778 -303.0083) 
(list 1280.0787 -301.35) 
(list 1280.0797 -299.6917) 
(list 1280.0807 -298.0333) 
(list 1280.0817 -296.375) 
(list 1280.0828 -294.7167) 
(list 1280.0839 -293.0583) 
(list 1280.085 -291.4) 
(list 1280.0862 -289.7417) 
(list 1280.0874 -288.0833) 
(list 1280.0886 -286.425) 
(list 1280.0899 -284.7667) 
(list 1280.0912 -283.1083) 
(list 1280.0925 -281.45) 
(list 1280.0939 -279.7917) 
(list 1280.0953 -278.1333) 
(list 1280.0967 -276.475) 
(list 1280.0982 -274.8167) 
(list 1280.0997 -273.1583) 
(list 1280.1012 -271.5) 
(list 1280.1028 -269.8417) 
(list 1280.1044 -268.1833) 
(list 1280.1061 -266.525) 
(list 1280.1078 -264.8667) 
(list 1280.1095 -263.2083) 
(list 1280.1113 -261.55) 
(list 1280.1131 -259.8917) 
(list 1280.115 -258.2333) 
(list 1280.1168 -256.575) 
(list 1280.1188 -254.9167) 
(list 1280.1208 -253.2583) 
(list 1280.1228 -251.6) 
(list 1280.1248 -249.9417) 
(list 1280.1269 -248.2833) 
(list 1280.1291 -246.625) 
(list 1280.1313 -244.9667) 
(list 1280.1335 -243.3083) 
(list 1280.1358 -241.65) 
(list 1280.1381 -239.9917) 
(list 1280.1405 -238.3333) 
(list 1280.1429 -236.675) 
(list 1280.1454 -235.0167) 
(list 1280.1479 -233.3583) 
(list 1280.1504 -231.7) 
(list 1280.1531 -230.0417) 
(list 1280.1557 -228.3833) 
(list 1280.1584 -226.725) 
(list 1280.1612 -225.0667) 
(list 1280.164 -223.4083) 
(list 1280.1668 -221.75) 
(list 1280.1697 -220.0917) 
(list 1280.1727 -218.4333) 
(list 1280.1757 -216.775) 
(list 1280.1787 -215.1167) 
(list 1280.1818 -213.4583) 
(list 1280.185 -211.8) 
(list 1279.815 -211.8) 
(list 1279.8182 -213.4583) 
(list 1279.8213 -215.1167) 
(list 1279.8243 -216.775) 
(list 1279.8273 -218.4333) 
(list 1279.8303 -220.0917) 
(list 1279.8332 -221.75) 
(list 1279.836 -223.4083) 
(list 1279.8388 -225.0667) 
(list 1279.8416 -226.725) 
(list 1279.8443 -228.3833) 
(list 1279.8469 -230.0417) 
(list 1279.8496 -231.7) 
(list 1279.8521 -233.3583) 
(list 1279.8546 -235.0167) 
(list 1279.8571 -236.675) 
(list 1279.8595 -238.3333) 
(list 1279.8619 -239.9917) 
(list 1279.8642 -241.65) 
(list 1279.8665 -243.3083) 
(list 1279.8687 -244.9667) 
(list 1279.8709 -246.625) 
(list 1279.8731 -248.2833) 
(list 1279.8752 -249.9417) 
(list 1279.8772 -251.6) 
(list 1279.8792 -253.2583) 
(list 1279.8812 -254.9167) 
(list 1279.8832 -256.575) 
(list 1279.885 -258.2333) 
(list 1279.8869 -259.8917) 
(list 1279.8887 -261.55) 
(list 1279.8905 -263.2083) 
(list 1279.8922 -264.8667) 
(list 1279.8939 -266.525) 
(list 1279.8956 -268.1833) 
(list 1279.8972 -269.8417) 
(list 1279.8988 -271.5) 
(list 1279.9003 -273.1583) 
(list 1279.9018 -274.8167) 
(list 1279.9033 -276.475) 
(list 1279.9047 -278.1333) 
(list 1279.9061 -279.7917) 
(list 1279.9075 -281.45) 
(list 1279.9088 -283.1083) 
(list 1279.9101 -284.7667) 
(list 1279.9114 -286.425) 
(list 1279.9126 -288.0833) 
(list 1279.9138 -289.7417) 
(list 1279.915 -291.4) 
(list 1279.9161 -293.0583) 
(list 1279.9172 -294.7167) 
(list 1279.9183 -296.375) 
(list 1279.9193 -298.0333) 
(list 1279.9203 -299.6917) 
(list 1279.9213 -301.35) 
(list 1279.9222 -303.0083) 
(list 1279.9232 -304.6667) 
(list 1279.9241 -306.325) 
(list 1279.9249 -307.9833) 
(list 1279.9258 -309.6417) 
(list 1279.9266 -311.3) 
(list 1279.9273 -312.9583) 
(list 1279.9281 -314.6167) 
(list 1279.9288 -316.275) 
(list 1279.9295 -317.9333) 
(list 1279.9302 -319.5917) 
(list 1279.9309 -321.25) 
(list 1279.9315 -322.9083) 
(list 1279.9321 -324.5667) 
(list 1279.9327 -326.225) 
(list 1279.9333 -327.8833) 
(list 1279.9338 -329.5417) 
(list 1279.9343 -331.2) 
(list 1279.9348 -332.8583) 
(list 1279.9353 -334.5167) 
(list 1279.9358 -336.175) 
(list 1279.9362 -337.8333) 
(list 1279.9366 -339.4917) 
(list 1279.937 -341.15) 
(list 1279.9374 -342.8083) 
(list 1279.9378 -344.4667) 
(list 1279.9381 -346.125) 
(list 1279.9385 -347.7833) 
(list 1279.9388 -349.4417) 
(list 1279.9391 -351.1) 
(list 1279.9393 -352.7583) 
(list 1279.9396 -354.4167) 
(list 1279.9398 -356.075) 
(list 1279.9401 -357.7333) 
(list 1279.9403 -359.3917) 
(list 1279.9405 -361.05) 
(list 1279.9407 -362.7083) 
(list 1279.9409 -364.3667) 
(list 1279.941 -366.025) 
(list 1279.9412 -367.6833) 
(list 1279.9413 -369.3417) 
(list 1279.9415 -371) 
(list 1279.9416 -372.6583) 
(list 1279.9417 -374.3167) 
(list 1279.9418 -375.975) 
(list 1279.9419 -377.6333) 
(list 1279.942 -379.2917) 
(list 1279.9421 -380.95) 
(list 1279.9421 -382.6083) 
(list 1279.9422 -384.2667) 
(list 1279.9423 -385.925) 
(list 1279.9423 -387.5833) 
(list 1279.9423 -389.2417) 
(list 1279.9424 -390.9) 
(list 1279.9424 -392.5583) 
(list 1279.9424 -394.2167) 
(list 1279.9424 -395.875) 
(list 1279.9425 -397.5333) 
(list 1279.9425 -399.1917) 
(list 1279.9425 -400.85) 
(list 1279.9425 -402.5083) 
(list 1279.9425 -404.1667) 
(list 1279.9425 -405.825) 
(list 1279.9425 -407.4833) 
(list 1279.9425 -409.1417) 
(list 1279.9425 -410.8)))
(apply 'command (append '("pline") coords '("c")))
(setq currobj (ssadd (entlast) currobj))
(command "_layer" "set" "prebias" "")
(command "_rectangle" "1279.815,-410.8" "1280.185,-211.8")
(setq currobj (ssadd (entlast) currobj))
(command "_layer" "set" "nitride" "")
(setq singlenanobeam4 currobj)
(setq currobj nil)
(setq currobj (ssadd))
; DRAWING NODE ARRAY
(setq coords (list 
(list 1280.185 -211.8) 
(list 1280.5625 -201.8) 
(list 1280.5625 -201.8) 
(list 1280.5625 -200.8) 
(list 1354.585 -212.6864) 
(list 1354.585 -207.7434) 
(list 1280.5625 -197.357) 
(list 1280.5625 -196.357) 
(list 1280.5625 -196.357) 
(list 1280.2625 -186.357) 
(list 1279.7375 -186.357) 
(list 1279.4375 -196.357) 
(list 1279.4375 -196.357) 
(list 1279.4375 -197.357) 
(list 1205.415 -207.7434) 
(list 1205.415 -212.6864) 
(list 1279.4375 -200.8) 
(list 1279.4375 -201.8) 
(list 1279.4375 -201.8) 
(list 1279.815 -211.8)))
(apply 'command (append '("pline") coords '("c")))
(setq currobj (ssadd (entlast) currobj))
(command "_layer" "set" "prebias" "")
(setq coords (list 
(list 1279.4375 -212.6864) 
(list 1279.4375 -200.8) 
(list 1205.415 -212.6864) 
(list 1205.415 -207.7434) 
(list 1279.4375 -197.357) 
(list 1279.4375 -186.357) 
(list 1280.5625 -186.357) 
(list 1280.5625 -197.357) 
(list 1354.585 -207.7434) 
(list 1354.585 -212.6864) 
(list 1280.5625 -200.8) 
(list 1280.5625 -212.6864)))
(apply 'command (append '("pline") coords '("c")))
(setq currobj (ssadd (entlast) currobj))
(command "_layer" "set" "nitride" "")
(command "_layer" "set" "fda1" "")
(setq coords (list 
(list 1280.5625 -200.657) 
(list 1354.585 -212.5434) 
(list 1354.585 -212.3664) 
(list 1280.5625 -200.58)))
(apply 'command (append '("pline") coords '("c")))
(setq currobj (ssadd (entlast) currobj))
(setq coords (list 
(list 1280.5625 -200.437) 
(list 1354.585 -212.2234) 
(list 1354.585 -212.0464) 
(list 1280.5625 -200.36)))
(apply 'command (append '("pline") coords '("c")))
(setq currobj (ssadd (entlast) currobj))
(setq coords (list 
(list 1280.5625 -200.217) 
(list 1354.585 -211.9034) 
(list 1354.585 -211.7264) 
(list 1280.5625 -200.14)))
(apply 'command (append '("pline") coords '("c")))
(setq currobj (ssadd (entlast) currobj))
(setq coords (list 
(list 1280.5625 -199.997) 
(list 1354.585 -211.5834) 
(list 1354.585 -211.4064) 
(list 1280.5625 -199.92)))
(apply 'command (append '("pline") coords '("c")))
(setq currobj (ssadd (entlast) currobj))
(setq coords (list 
(list 1280.5625 -199.777) 
(list 1354.585 -211.2634) 
(list 1354.585 -211.0864) 
(list 1280.5625 -199.7)))
(apply 'command (append '("pline") coords '("c")))
(setq currobj (ssadd (entlast) currobj))
(setq coords (list 
(list 1280.5625 -199.557) 
(list 1354.585 -210.9434) 
(list 1354.585 -210.7664) 
(list 1280.5625 -199.48)))
(apply 'command (append '("pline") coords '("c")))
(setq currobj (ssadd (entlast) currobj))
(setq coords (list 
(list 1280.5625 -199.337) 
(list 1354.585 -210.6234) 
(list 1354.585 -210.4464) 
(list 1280.5625 -199.26)))
(apply 'command (append '("pline") coords '("c")))
(setq currobj (ssadd (entlast) currobj))
(setq coords (list 
(list 1280.5625 -199.117) 
(list 1354.585 -210.3034) 
(list 1354.585 -210.1264) 
(list 1280.5625 -199.04)))
(apply 'command (append '("pline") coords '("c")))
(setq currobj (ssadd (entlast) currobj))
(setq coords (list 
(list 1280.5625 -198.897) 
(list 1354.585 -209.9834) 
(list 1354.585 -209.8064) 
(list 1280.5625 -198.82)))
(apply 'command (append '("pline") coords '("c")))
(setq currobj (ssadd (entlast) currobj))
(setq coords (list 
(list 1280.5625 -198.677) 
(list 1354.585 -209.6634) 
(list 1354.585 -209.4864) 
(list 1280.5625 -198.6)))
(apply 'command (append '("pline") coords '("c")))
(setq currobj (ssadd (entlast) currobj))
(setq coords (list 
(list 1280.5625 -198.457) 
(list 1354.585 -209.3434) 
(list 1354.585 -209.1664) 
(list 1280.5625 -198.38)))
(apply 'command (append '("pline") coords '("c")))
(setq currobj (ssadd (entlast) currobj))
(setq coords (list 
(list 1280.5625 -198.237) 
(list 1354.585 -209.0234) 
(list 1354.585 -208.8464) 
(list 1280.5625 -198.16)))
(apply 'command (append '("pline") coords '("c")))
(setq currobj (ssadd (entlast) currobj))
(setq coords (list 
(list 1280.5625 -198.017) 
(list 1354.585 -208.7034) 
(list 1354.585 -208.5264) 
(list 1280.5625 -197.94)))
(apply 'command (append '("pline") coords '("c")))
(setq currobj (ssadd (entlast) currobj))
(setq coords (list 
(list 1280.5625 -197.797) 
(list 1354.585 -208.3834) 
(list 1354.585 -208.2064) 
(list 1280.5625 -197.72)))
(apply 'command (append '("pline") coords '("c")))
(setq currobj (ssadd (entlast) currobj))
(setq coords (list 
(list 1280.5625 -197.577) 
(list 1354.585 -208.0634) 
(list 1354.585 -207.8864) 
(list 1280.5625 -197.5)))
(apply 'command (append '("pline") coords '("c")))
(setq currobj (ssadd (entlast) currobj))
(setq coords (list 
(list 1279.4375 -197.5) 
(list 1205.415 -207.8864) 
(list 1205.415 -208.0634) 
(list 1279.4375 -197.577)))
(apply 'command (append '("pline") coords '("c")))
(setq currobj (ssadd (entlast) currobj))
(setq coords (list 
(list 1279.4375 -197.72) 
(list 1205.415 -208.2064) 
(list 1205.415 -208.3834) 
(list 1279.4375 -197.797)))
(apply 'command (append '("pline") coords '("c")))
(setq currobj (ssadd (entlast) currobj))
(setq coords (list 
(list 1279.4375 -197.94) 
(list 1205.415 -208.5264) 
(list 1205.415 -208.7034) 
(list 1279.4375 -198.017)))
(apply 'command (append '("pline") coords '("c")))
(setq currobj (ssadd (entlast) currobj))
(setq coords (list 
(list 1279.4375 -198.16) 
(list 1205.415 -208.8464) 
(list 1205.415 -209.0234) 
(list 1279.4375 -198.237)))
(apply 'command (append '("pline") coords '("c")))
(setq currobj (ssadd (entlast) currobj))
(setq coords (list 
(list 1279.4375 -198.38) 
(list 1205.415 -209.1664) 
(list 1205.415 -209.3434) 
(list 1279.4375 -198.457)))
(apply 'command (append '("pline") coords '("c")))
(setq currobj (ssadd (entlast) currobj))
(setq coords (list 
(list 1279.4375 -198.6) 
(list 1205.415 -209.4864) 
(list 1205.415 -209.6634) 
(list 1279.4375 -198.677)))
(apply 'command (append '("pline") coords '("c")))
(setq currobj (ssadd (entlast) currobj))
(setq coords (list 
(list 1279.4375 -198.82) 
(list 1205.415 -209.8064) 
(list 1205.415 -209.9834) 
(list 1279.4375 -198.897)))
(apply 'command (append '("pline") coords '("c")))
(setq currobj (ssadd (entlast) currobj))
(setq coords (list 
(list 1279.4375 -199.04) 
(list 1205.415 -210.1264) 
(list 1205.415 -210.3034) 
(list 1279.4375 -199.117)))
(apply 'command (append '("pline") coords '("c")))
(setq currobj (ssadd (entlast) currobj))
(setq coords (list 
(list 1279.4375 -199.26) 
(list 1205.415 -210.4464) 
(list 1205.415 -210.6234) 
(list 1279.4375 -199.337)))
(apply 'command (append '("pline") coords '("c")))
(setq currobj (ssadd (entlast) currobj))
(setq coords (list 
(list 1279.4375 -199.48) 
(list 1205.415 -210.7664) 
(list 1205.415 -210.9434) 
(list 1279.4375 -199.557)))
(apply 'command (append '("pline") coords '("c")))
(setq currobj (ssadd (entlast) currobj))
(setq coords (list 
(list 1279.4375 -199.7) 
(list 1205.415 -211.0864) 
(list 1205.415 -211.2634) 
(list 1279.4375 -199.777)))
(apply 'command (append '("pline") coords '("c")))
(setq currobj (ssadd (entlast) currobj))
(setq coords (list 
(list 1279.4375 -199.92) 
(list 1205.415 -211.4064) 
(list 1205.415 -211.5834) 
(list 1279.4375 -199.997)))
(apply 'command (append '("pline") coords '("c")))
(setq currobj (ssadd (entlast) currobj))
(setq coords (list 
(list 1279.4375 -200.14) 
(list 1205.415 -211.7264) 
(list 1205.415 -211.9034) 
(list 1279.4375 -200.217)))
(apply 'command (append '("pline") coords '("c")))
(setq currobj (ssadd (entlast) currobj))
(setq coords (list 
(list 1279.4375 -200.36) 
(list 1205.415 -212.0464) 
(list 1205.415 -212.2234) 
(list 1279.4375 -200.437)))
(apply 'command (append '("pline") coords '("c")))
(setq currobj (ssadd (entlast) currobj))
(setq coords (list 
(list 1279.4375 -200.58) 
(list 1205.415 -212.3664) 
(list 1205.415 -212.5434) 
(list 1279.4375 -200.657)))
(apply 'command (append '("pline") coords '("c")))
(setq currobj (ssadd (entlast) currobj))
(command "_layer" "set" "nitride" "")
(command "_layer" "set" "text" "")
(command "_circle" "1278.985,-211.8" "0.075")
(command "_circle" "1278.985,-211.5" "0.075")
(command "_circle" "1278.985,-211.2" "0.075")
(command "_circle" "1278.985,-210.9" "0.075")
(command "_circle" "1278.985,-210.6" "0.075")
(command "_circle" "1278.685,-211.8" "0.075")
(command "_circle" "1278.685,-211.5" "0.075")
(command "_circle" "1278.685,-211.2" "0.075")
(command "_circle" "1278.685,-210.9" "0.075")
(command "_circle" "1278.685,-210.6" "0.075")
(command "_circle" "1278.385,-211.8" "0.075")
(command "_circle" "1278.385,-211.5" "0.075")
(command "_circle" "1278.385,-211.2" "0.075")
(command "_circle" "1278.385,-210.9" "0.075")
(command "_circle" "1278.385,-210.6" "0.075")
(command "_circle" "1278.085,-211.8" "0.075")
(command "_circle" "1278.085,-211.5" "0.075")
(command "_circle" "1278.085,-211.2" "0.075")
(command "_circle" "1278.085,-210.9" "0.075")
(command "_circle" "1278.085,-210.6" "0.075")
(command "_circle" "1277.785,-211.8" "0.075")
(command "_circle" "1277.785,-211.5" "0.075")
(command "_circle" "1277.785,-211.2" "0.075")
(command "_circle" "1277.785,-210.9" "0.075")
(command "_circle" "1277.785,-210.6" "0.075")
(command "_layer" "set" "nitride" "")
(setq anglednodearray4 currobj)
(setq currobj nil)
(setq currobj (ssadd))
; DRAWING COOLED SINGLE NANOBEAM
(setq coords (list 
(list 1280.2625 -186.357) 
(list 1280.2625 -181.357) 
(list 1279.7375 -181.357) 
(list 1279.7375 -186.357)))
(apply 'command (append '("pline") coords '("c")))
(setq currobj (ssadd (entlast) currobj))
(command "_layer" "set" "prebias" "")
(command "_rectangle" "1279.7375,-186.357" "1280.2625,-181.357")
(setq currobj (ssadd (entlast) currobj))
(command "_layer" "set" "nitride" "")
(setq coords (list 
(list 1280.2625 -181.357) 
(list 1280.5625 -171.357) 
(list 1280.5625 -171.357) 
(list 1280.5625 -170.357) 
(list 1354.585 -171.107) 
(list 1354.585 -166.164) 
(list 1280.5625 -166.914) 
(list 1280.5625 -165.914) 
(list 1280.5625 -165.914) 
(list 1280.2625 -155.914) 
(list 1279.7375 -155.914) 
(list 1279.4375 -165.914) 
(list 1279.4375 -165.914) 
(list 1279.4375 -166.914) 
(list 1205.415 -166.164) 
(list 1205.415 -171.107) 
(list 1279.4375 -170.357) 
(list 1279.4375 -171.357) 
(list 1279.4375 -171.357) 
(list 1279.7375 -181.357)))
(apply 'command (append '("pline") coords '("c")))
(setq currobj (ssadd (entlast) currobj))
(command "_layer" "set" "prebias" "")
(setq coords (list 
(list 1279.4375 -181.357) 
(list 1279.4375 -170.357) 
(list 1205.415 -171.107) 
(list 1205.415 -166.164) 
(list 1279.4375 -166.914) 
(list 1279.4375 -155.914) 
(list 1280.5625 -155.914) 
(list 1280.5625 -166.914) 
(list 1354.585 -166.164) 
(list 1354.585 -171.107) 
(list 1280.5625 -170.357) 
(list 1280.5625 -181.357)))
(apply 'command (append '("pline") coords '("c")))
(setq currobj (ssadd (entlast) currobj))
(command "_layer" "set" "nitride" "")
(command "_layer" "set" "fda1" "")
(setq coords (list 
(list 1280.5625 -170.214) 
(list 1354.585 -170.964) 
(list 1354.585 -170.787) 
(list 1280.5625 -170.137)))
(apply 'command (append '("pline") coords '("c")))
(setq currobj (ssadd (entlast) currobj))
(setq coords (list 
(list 1280.5625 -169.994) 
(list 1354.585 -170.644) 
(list 1354.585 -170.467) 
(list 1280.5625 -169.917)))
(apply 'command (append '("pline") coords '("c")))
(setq currobj (ssadd (entlast) currobj))
(setq coords (list 
(list 1280.5625 -169.774) 
(list 1354.585 -170.324) 
(list 1354.585 -170.147) 
(list 1280.5625 -169.697)))
(apply 'command (append '("pline") coords '("c")))
(setq currobj (ssadd (entlast) currobj))
(setq coords (list 
(list 1280.5625 -169.554) 
(list 1354.585 -170.004) 
(list 1354.585 -169.827) 
(list 1280.5625 -169.477)))
(apply 'command (append '("pline") coords '("c")))
(setq currobj (ssadd (entlast) currobj))
(setq coords (list 
(list 1280.5625 -169.334) 
(list 1354.585 -169.684) 
(list 1354.585 -169.507) 
(list 1280.5625 -169.257)))
(apply 'command (append '("pline") coords '("c")))
(setq currobj (ssadd (entlast) currobj))
(setq coords (list 
(list 1280.5625 -169.114) 
(list 1354.585 -169.364) 
(list 1354.585 -169.187) 
(list 1280.5625 -169.037)))
(apply 'command (append '("pline") coords '("c")))
(setq currobj (ssadd (entlast) currobj))
(setq coords (list 
(list 1280.5625 -168.894) 
(list 1354.585 -169.044) 
(list 1354.585 -168.867) 
(list 1280.5625 -168.817)))
(apply 'command (append '("pline") coords '("c")))
(setq currobj (ssadd (entlast) currobj))
(setq coords (list 
(list 1280.5625 -168.674) 
(list 1354.585 -168.724) 
(list 1354.585 -168.547) 
(list 1280.5625 -168.597)))
(apply 'command (append '("pline") coords '("c")))
(setq currobj (ssadd (entlast) currobj))
(setq coords (list 
(list 1280.5625 -168.454) 
(list 1354.585 -168.404) 
(list 1354.585 -168.227) 
(list 1280.5625 -168.377)))
(apply 'command (append '("pline") coords '("c")))
(setq currobj (ssadd (entlast) currobj))
(setq coords (list 
(list 1280.5625 -168.234) 
(list 1354.585 -168.084) 
(list 1354.585 -167.907) 
(list 1280.5625 -168.157)))
(apply 'command (append '("pline") coords '("c")))
(setq currobj (ssadd (entlast) currobj))
(setq coords (list 
(list 1280.5625 -168.014) 
(list 1354.585 -167.764) 
(list 1354.585 -167.587) 
(list 1280.5625 -167.937)))
(apply 'command (append '("pline") coords '("c")))
(setq currobj (ssadd (entlast) currobj))
(setq coords (list 
(list 1280.5625 -167.794) 
(list 1354.585 -167.444) 
(list 1354.585 -167.267) 
(list 1280.5625 -167.717)))
(apply 'command (append '("pline") coords '("c")))
(setq currobj (ssadd (entlast) currobj))
(setq coords (list 
(list 1280.5625 -167.574) 
(list 1354.585 -167.124) 
(list 1354.585 -166.947) 
(list 1280.5625 -167.497)))
(apply 'command (append '("pline") coords '("c")))
(setq currobj (ssadd (entlast) currobj))
(setq coords (list 
(list 1280.5625 -167.354) 
(list 1354.585 -166.804) 
(list 1354.585 -166.627) 
(list 1280.5625 -167.277)))
(apply 'command (append '("pline") coords '("c")))
(setq currobj (ssadd (entlast) currobj))
(setq coords (list 
(list 1280.5625 -167.134) 
(list 1354.585 -166.484) 
(list 1354.585 -166.307) 
(list 1280.5625 -167.057)))
(apply 'command (append '("pline") coords '("c")))
(setq currobj (ssadd (entlast) currobj))
(setq coords (list 
(list 1279.4375 -167.057) 
(list 1205.415 -166.307) 
(list 1205.415 -166.484) 
(list 1279.4375 -167.134)))
(apply 'command (append '("pline") coords '("c")))
(setq currobj (ssadd (entlast) currobj))
(setq coords (list 
(list 1279.4375 -167.277) 
(list 1205.415 -166.627) 
(list 1205.415 -166.804) 
(list 1279.4375 -167.354)))
(apply 'command (append '("pline") coords '("c")))
(setq currobj (ssadd (entlast) currobj))
(setq coords (list 
(list 1279.4375 -167.497) 
(list 1205.415 -166.947) 
(list 1205.415 -167.124) 
(list 1279.4375 -167.574)))
(apply 'command (append '("pline") coords '("c")))
(setq currobj (ssadd (entlast) currobj))
(setq coords (list 
(list 1279.4375 -167.717) 
(list 1205.415 -167.267) 
(list 1205.415 -167.444) 
(list 1279.4375 -167.794)))
(apply 'command (append '("pline") coords '("c")))
(setq currobj (ssadd (entlast) currobj))
(setq coords (list 
(list 1279.4375 -167.937) 
(list 1205.415 -167.587) 
(list 1205.415 -167.764) 
(list 1279.4375 -168.014)))
(apply 'command (append '("pline") coords '("c")))
(setq currobj (ssadd (entlast) currobj))
(setq coords (list 
(list 1279.4375 -168.157) 
(list 1205.415 -167.907) 
(list 1205.415 -168.084) 
(list 1279.4375 -168.234)))
(apply 'command (append '("pline") coords '("c")))
(setq currobj (ssadd (entlast) currobj))
(setq coords (list 
(list 1279.4375 -168.377) 
(list 1205.415 -168.227) 
(list 1205.415 -168.404) 
(list 1279.4375 -168.454)))
(apply 'command (append '("pline") coords '("c")))
(setq currobj (ssadd (entlast) currobj))
(setq coords (list 
(list 1279.4375 -168.597) 
(list 1205.415 -168.547) 
(list 1205.415 -168.724) 
(list 1279.4375 -168.674)))
(apply 'command (append '("pline") coords '("c")))
(setq currobj (ssadd (entlast) currobj))
(setq coords (list 
(list 1279.4375 -168.817) 
(list 1205.415 -168.867) 
(list 1205.415 -169.044) 
(list 1279.4375 -168.894)))
(apply 'command (append '("pline") coords '("c")))
(setq currobj (ssadd (entlast) currobj))
(setq coords (list 
(list 1279.4375 -169.037) 
(list 1205.415 -169.187) 
(list 1205.415 -169.364) 
(list 1279.4375 -169.114)))
(apply 'command (append '("pline") coords '("c")))
(setq currobj (ssadd (entlast) currobj))
(setq coords (list 
(list 1279.4375 -169.257) 
(list 1205.415 -169.507) 
(list 1205.415 -169.684) 
(list 1279.4375 -169.334)))
(apply 'command (append '("pline") coords '("c")))
(setq currobj (ssadd (entlast) currobj))
(setq coords (list 
(list 1279.4375 -169.477) 
(list 1205.415 -169.827) 
(list 1205.415 -170.004) 
(list 1279.4375 -169.554)))
(apply 'command (append '("pline") coords '("c")))
(setq currobj (ssadd (entlast) currobj))
(setq coords (list 
(list 1279.4375 -169.697) 
(list 1205.415 -170.147) 
(list 1205.415 -170.324) 
(list 1279.4375 -169.774)))
(apply 'command (append '("pline") coords '("c")))
(setq currobj (ssadd (entlast) currobj))
(setq coords (list 
(list 1279.4375 -169.917) 
(list 1205.415 -170.467) 
(list 1205.415 -170.644) 
(list 1279.4375 -169.994)))
(apply 'command (append '("pline") coords '("c")))
(setq currobj (ssadd (entlast) currobj))
(setq coords (list 
(list 1279.4375 -170.137) 
(list 1205.415 -170.787) 
(list 1205.415 -170.964) 
(list 1279.4375 -170.214)))
(apply 'command (append '("pline") coords '("c")))
(setq currobj (ssadd (entlast) currobj))
(command "_layer" "set" "nitride" "")
(command "_layer" "set" "text" "")
(command "_circle" "1279.0625,-181.357" "0.075")
(command "_circle" "1279.0625,-181.057" "0.075")
(command "_circle" "1279.0625,-180.757" "0.075")
(command "_circle" "1279.0625,-180.457" "0.075")
(command "_circle" "1279.0625,-180.157" "0.075")
(command "_circle" "1278.7625,-181.357" "0.075")
(command "_circle" "1278.7625,-181.057" "0.075")
(command "_circle" "1278.7625,-180.757" "0.075")
(command "_circle" "1278.7625,-180.457" "0.075")
(command "_circle" "1278.7625,-180.157" "0.075")
(command "_circle" "1278.4625,-181.357" "0.075")
(command "_circle" "1278.4625,-181.057" "0.075")
(command "_circle" "1278.4625,-180.757" "0.075")
(command "_circle" "1278.4625,-180.457" "0.075")
(command "_circle" "1278.4625,-180.157" "0.075")
(command "_circle" "1278.1625,-181.357" "0.075")
(command "_circle" "1278.1625,-181.057" "0.075")
(command "_circle" "1278.1625,-180.757" "0.075")
(command "_circle" "1278.1625,-180.457" "0.075")
(command "_circle" "1278.1625,-180.157" "0.075")
(command "_circle" "1277.8625,-181.357" "0.075")
(command "_circle" "1277.8625,-181.057" "0.075")
(command "_circle" "1277.8625,-180.757" "0.075")
(command "_circle" "1277.8625,-180.457" "0.075")
(command "_circle" "1277.8625,-180.157" "0.075")
(command "_layer" "set" "nitride" "")
(setq coords (list 
(list 1280.2625 -155.914) 
(list 1280.2625 -40.2693) 
(list 1279.7375 -40.2693) 
(list 1279.7375 -155.914)))
(apply 'command (append '("pline") coords '("c")))
(setq currobj (ssadd (entlast) currobj))
(command "_layer" "set" "prebias" "")
(command "_rectangle" "1279.7375,-155.914" "1280.2625,-40.2693")
(setq currobj (ssadd (entlast) currobj))
(command "_layer" "set" "nitride" "")
(setq coords (list 
(list 1280.2625 -40.2693) 
(list 1280.5625 -30.2693) 
(list 1280.5625 -30.2693) 
(list 1280.5625 -29.2693) 
(list 1354.585 -30.0193) 
(list 1354.585 -25.0763) 
(list 1280.5625 -25.8263) 
(list 1280.5625 -24.8263) 
(list 1280.5625 -24.8263) 
(list 1280.2625 -14.8263) 
(list 1279.7375 -14.8263) 
(list 1279.4375 -24.8263) 
(list 1279.4375 -24.8263) 
(list 1279.4375 -25.8263) 
(list 1205.415 -25.0763) 
(list 1205.415 -30.0193) 
(list 1279.4375 -29.2693) 
(list 1279.4375 -30.2693) 
(list 1279.4375 -30.2693) 
(list 1279.7375 -40.2693)))
(apply 'command (append '("pline") coords '("c")))
(setq currobj (ssadd (entlast) currobj))
(command "_layer" "set" "prebias" "")
(setq coords (list 
(list 1279.4375 -40.2693) 
(list 1279.4375 -29.2693) 
(list 1205.415 -30.0193) 
(list 1205.415 -25.0763) 
(list 1279.4375 -25.8263) 
(list 1279.4375 -14.8263) 
(list 1280.5625 -14.8263) 
(list 1280.5625 -25.8263) 
(list 1354.585 -25.0763) 
(list 1354.585 -30.0193) 
(list 1280.5625 -29.2693) 
(list 1280.5625 -40.2693)))
(apply 'command (append '("pline") coords '("c")))
(setq currobj (ssadd (entlast) currobj))
(command "_layer" "set" "nitride" "")
(command "_layer" "set" "fda1" "")
(setq coords (list 
(list 1280.5625 -29.1263) 
(list 1354.585 -29.8763) 
(list 1354.585 -29.6993) 
(list 1280.5625 -29.0493)))
(apply 'command (append '("pline") coords '("c")))
(setq currobj (ssadd (entlast) currobj))
(setq coords (list 
(list 1280.5625 -28.9063) 
(list 1354.585 -29.5563) 
(list 1354.585 -29.3793) 
(list 1280.5625 -28.8293)))
(apply 'command (append '("pline") coords '("c")))
(setq currobj (ssadd (entlast) currobj))
(setq coords (list 
(list 1280.5625 -28.6863) 
(list 1354.585 -29.2363) 
(list 1354.585 -29.0593) 
(list 1280.5625 -28.6093)))
(apply 'command (append '("pline") coords '("c")))
(setq currobj (ssadd (entlast) currobj))
(setq coords (list 
(list 1280.5625 -28.4663) 
(list 1354.585 -28.9163) 
(list 1354.585 -28.7393) 
(list 1280.5625 -28.3893)))
(apply 'command (append '("pline") coords '("c")))
(setq currobj (ssadd (entlast) currobj))
(setq coords (list 
(list 1280.5625 -28.2463) 
(list 1354.585 -28.5963) 
(list 1354.585 -28.4193) 
(list 1280.5625 -28.1693)))
(apply 'command (append '("pline") coords '("c")))
(setq currobj (ssadd (entlast) currobj))
(setq coords (list 
(list 1280.5625 -28.0263) 
(list 1354.585 -28.2763) 
(list 1354.585 -28.0993) 
(list 1280.5625 -27.9493)))
(apply 'command (append '("pline") coords '("c")))
(setq currobj (ssadd (entlast) currobj))
(setq coords (list 
(list 1280.5625 -27.8063) 
(list 1354.585 -27.9563) 
(list 1354.585 -27.7793) 
(list 1280.5625 -27.7293)))
(apply 'command (append '("pline") coords '("c")))
(setq currobj (ssadd (entlast) currobj))
(setq coords (list 
(list 1280.5625 -27.5863) 
(list 1354.585 -27.6363) 
(list 1354.585 -27.4593) 
(list 1280.5625 -27.5093)))
(apply 'command (append '("pline") coords '("c")))
(setq currobj (ssadd (entlast) currobj))
(setq coords (list 
(list 1280.5625 -27.3663) 
(list 1354.585 -27.3163) 
(list 1354.585 -27.1393) 
(list 1280.5625 -27.2893)))
(apply 'command (append '("pline") coords '("c")))
(setq currobj (ssadd (entlast) currobj))
(setq coords (list 
(list 1280.5625 -27.1463) 
(list 1354.585 -26.9963) 
(list 1354.585 -26.8193) 
(list 1280.5625 -27.0693)))
(apply 'command (append '("pline") coords '("c")))
(setq currobj (ssadd (entlast) currobj))
(setq coords (list 
(list 1280.5625 -26.9263) 
(list 1354.585 -26.6763) 
(list 1354.585 -26.4993) 
(list 1280.5625 -26.8493)))
(apply 'command (append '("pline") coords '("c")))
(setq currobj (ssadd (entlast) currobj))
(setq coords (list 
(list 1280.5625 -26.7063) 
(list 1354.585 -26.3563) 
(list 1354.585 -26.1793) 
(list 1280.5625 -26.6293)))
(apply 'command (append '("pline") coords '("c")))
(setq currobj (ssadd (entlast) currobj))
(setq coords (list 
(list 1280.5625 -26.4863) 
(list 1354.585 -26.0363) 
(list 1354.585 -25.8593) 
(list 1280.5625 -26.4093)))
(apply 'command (append '("pline") coords '("c")))
(setq currobj (ssadd (entlast) currobj))
(setq coords (list 
(list 1280.5625 -26.2663) 
(list 1354.585 -25.7163) 
(list 1354.585 -25.5393) 
(list 1280.5625 -26.1893)))
(apply 'command (append '("pline") coords '("c")))
(setq currobj (ssadd (entlast) currobj))
(setq coords (list 
(list 1280.5625 -26.0463) 
(list 1354.585 -25.3963) 
(list 1354.585 -25.2193) 
(list 1280.5625 -25.9693)))
(apply 'command (append '("pline") coords '("c")))
(setq currobj (ssadd (entlast) currobj))
(setq coords (list 
(list 1279.4375 -25.9693) 
(list 1205.415 -25.2193) 
(list 1205.415 -25.3963) 
(list 1279.4375 -26.0463)))
(apply 'command (append '("pline") coords '("c")))
(setq currobj (ssadd (entlast) currobj))
(setq coords (list 
(list 1279.4375 -26.1893) 
(list 1205.415 -25.5393) 
(list 1205.415 -25.7163) 
(list 1279.4375 -26.2663)))
(apply 'command (append '("pline") coords '("c")))
(setq currobj (ssadd (entlast) currobj))
(setq coords (list 
(list 1279.4375 -26.4093) 
(list 1205.415 -25.8593) 
(list 1205.415 -26.0363) 
(list 1279.4375 -26.4863)))
(apply 'command (append '("pline") coords '("c")))
(setq currobj (ssadd (entlast) currobj))
(setq coords (list 
(list 1279.4375 -26.6293) 
(list 1205.415 -26.1793) 
(list 1205.415 -26.3563) 
(list 1279.4375 -26.7063)))
(apply 'command (append '("pline") coords '("c")))
(setq currobj (ssadd (entlast) currobj))
(setq coords (list 
(list 1279.4375 -26.8493) 
(list 1205.415 -26.4993) 
(list 1205.415 -26.6763) 
(list 1279.4375 -26.9263)))
(apply 'command (append '("pline") coords '("c")))
(setq currobj (ssadd (entlast) currobj))
(setq coords (list 
(list 1279.4375 -27.0693) 
(list 1205.415 -26.8193) 
(list 1205.415 -26.9963) 
(list 1279.4375 -27.1463)))
(apply 'command (append '("pline") coords '("c")))
(setq currobj (ssadd (entlast) currobj))
(setq coords (list 
(list 1279.4375 -27.2893) 
(list 1205.415 -27.1393) 
(list 1205.415 -27.3163) 
(list 1279.4375 -27.3663)))
(apply 'command (append '("pline") coords '("c")))
(setq currobj (ssadd (entlast) currobj))
(setq coords (list 
(list 1279.4375 -27.5093) 
(list 1205.415 -27.4593) 
(list 1205.415 -27.6363) 
(list 1279.4375 -27.5863)))
(apply 'command (append '("pline") coords '("c")))
(setq currobj (ssadd (entlast) currobj))
(setq coords (list 
(list 1279.4375 -27.7293) 
(list 1205.415 -27.7793) 
(list 1205.415 -27.9563) 
(list 1279.4375 -27.8063)))
(apply 'command (append '("pline") coords '("c")))
(setq currobj (ssadd (entlast) currobj))
(setq coords (list 
(list 1279.4375 -27.9493) 
(list 1205.415 -28.0993) 
(list 1205.415 -28.2763) 
(list 1279.4375 -28.0263)))
(apply 'command (append '("pline") coords '("c")))
(setq currobj (ssadd (entlast) currobj))
(setq coords (list 
(list 1279.4375 -28.1693) 
(list 1205.415 -28.4193) 
(list 1205.415 -28.5963) 
(list 1279.4375 -28.2463)))
(apply 'command (append '("pline") coords '("c")))
(setq currobj (ssadd (entlast) currobj))
(setq coords (list 
(list 1279.4375 -28.3893) 
(list 1205.415 -28.7393) 
(list 1205.415 -28.9163) 
(list 1279.4375 -28.4663)))
(apply 'command (append '("pline") coords '("c")))
(setq currobj (ssadd (entlast) currobj))
(setq coords (list 
(list 1279.4375 -28.6093) 
(list 1205.415 -29.0593) 
(list 1205.415 -29.2363) 
(list 1279.4375 -28.6863)))
(apply 'command (append '("pline") coords '("c")))
(setq currobj (ssadd (entlast) currobj))
(setq coords (list 
(list 1279.4375 -28.8293) 
(list 1205.415 -29.3793) 
(list 1205.415 -29.5563) 
(list 1279.4375 -28.9063)))
(apply 'command (append '("pline") coords '("c")))
(setq currobj (ssadd (entlast) currobj))
(setq coords (list 
(list 1279.4375 -29.0493) 
(list 1205.415 -29.6993) 
(list 1205.415 -29.8763) 
(list 1279.4375 -29.1263)))
(apply 'command (append '("pline") coords '("c")))
(setq currobj (ssadd (entlast) currobj))
(command "_layer" "set" "nitride" "")
(command "_layer" "set" "text" "")
(command "_circle" "1279.0625,-40.2693" "0.075")
(command "_circle" "1279.0625,-39.9693" "0.075")
(command "_circle" "1279.0625,-39.6693" "0.075")
(command "_circle" "1279.0625,-39.3693" "0.075")
(command "_circle" "1279.0625,-39.0693" "0.075")
(command "_circle" "1278.7625,-40.2693" "0.075")
(command "_circle" "1278.7625,-39.9693" "0.075")
(command "_circle" "1278.7625,-39.6693" "0.075")
(command "_circle" "1278.7625,-39.3693" "0.075")
(command "_circle" "1278.7625,-39.0693" "0.075")
(command "_circle" "1278.4625,-40.2693" "0.075")
(command "_circle" "1278.4625,-39.9693" "0.075")
(command "_circle" "1278.4625,-39.6693" "0.075")
(command "_circle" "1278.4625,-39.3693" "0.075")
(command "_circle" "1278.4625,-39.0693" "0.075")
(command "_circle" "1278.1625,-40.2693" "0.075")
(command "_circle" "1278.1625,-39.9693" "0.075")
(command "_circle" "1278.1625,-39.6693" "0.075")
(command "_circle" "1278.1625,-39.3693" "0.075")
(command "_circle" "1278.1625,-39.0693" "0.075")
(command "_circle" "1277.8625,-40.2693" "0.075")
(command "_circle" "1277.8625,-39.9693" "0.075")
(command "_circle" "1277.8625,-39.6693" "0.075")
(command "_circle" "1277.8625,-39.3693" "0.075")
(command "_circle" "1277.8625,-39.0693" "0.075")
(command "_layer" "set" "nitride" "")
(setq coords (list 
(list 1280.2625 -14.8263) 
(list 1280.2625 100.8184) 
(list 1279.7375 100.8184) 
(list 1279.7375 -14.8263)))
(apply 'command (append '("pline") coords '("c")))
(setq currobj (ssadd (entlast) currobj))
(command "_layer" "set" "prebias" "")
(command "_rectangle" "1279.7375,-14.8263" "1280.2625,100.8184")
(setq currobj (ssadd (entlast) currobj))
(command "_layer" "set" "nitride" "")
(setq coords (list 
(list 1280.2625 100.8184) 
(list 1280.5625 110.8184) 
(list 1280.5625 110.8184) 
(list 1280.5625 111.8184) 
(list 1354.585 111.0684) 
(list 1354.585 116.0114) 
(list 1280.5625 115.2614) 
(list 1280.5625 116.2614) 
(list 1280.5625 116.2614) 
(list 1280.2625 126.2614) 
(list 1279.7375 126.2614) 
(list 1279.4375 116.2614) 
(list 1279.4375 116.2614) 
(list 1279.4375 115.2614) 
(list 1205.415 116.0114) 
(list 1205.415 111.0684) 
(list 1279.4375 111.8184) 
(list 1279.4375 110.8184) 
(list 1279.4375 110.8184) 
(list 1279.7375 100.8184)))
(apply 'command (append '("pline") coords '("c")))
(setq currobj (ssadd (entlast) currobj))
(command "_layer" "set" "prebias" "")
(setq coords (list 
(list 1279.4375 100.8184) 
(list 1279.4375 111.8184) 
(list 1205.415 111.0684) 
(list 1205.415 116.0114) 
(list 1279.4375 115.2614) 
(list 1279.4375 126.2614) 
(list 1280.5625 126.2614) 
(list 1280.5625 115.2614) 
(list 1354.585 116.0114) 
(list 1354.585 111.0684) 
(list 1280.5625 111.8184) 
(list 1280.5625 100.8184)))
(apply 'command (append '("pline") coords '("c")))
(setq currobj (ssadd (entlast) currobj))
(command "_layer" "set" "nitride" "")
(command "_layer" "set" "fda1" "")
(setq coords (list 
(list 1280.5625 111.9614) 
(list 1354.585 111.2114) 
(list 1354.585 111.3884) 
(list 1280.5625 112.0384)))
(apply 'command (append '("pline") coords '("c")))
(setq currobj (ssadd (entlast) currobj))
(setq coords (list 
(list 1280.5625 112.1814) 
(list 1354.585 111.5314) 
(list 1354.585 111.7084) 
(list 1280.5625 112.2584)))
(apply 'command (append '("pline") coords '("c")))
(setq currobj (ssadd (entlast) currobj))
(setq coords (list 
(list 1280.5625 112.4014) 
(list 1354.585 111.8514) 
(list 1354.585 112.0284) 
(list 1280.5625 112.4784)))
(apply 'command (append '("pline") coords '("c")))
(setq currobj (ssadd (entlast) currobj))
(setq coords (list 
(list 1280.5625 112.6214) 
(list 1354.585 112.1714) 
(list 1354.585 112.3484) 
(list 1280.5625 112.6984)))
(apply 'command (append '("pline") coords '("c")))
(setq currobj (ssadd (entlast) currobj))
(setq coords (list 
(list 1280.5625 112.8414) 
(list 1354.585 112.4914) 
(list 1354.585 112.6684) 
(list 1280.5625 112.9184)))
(apply 'command (append '("pline") coords '("c")))
(setq currobj (ssadd (entlast) currobj))
(setq coords (list 
(list 1280.5625 113.0614) 
(list 1354.585 112.8114) 
(list 1354.585 112.9884) 
(list 1280.5625 113.1384)))
(apply 'command (append '("pline") coords '("c")))
(setq currobj (ssadd (entlast) currobj))
(setq coords (list 
(list 1280.5625 113.2814) 
(list 1354.585 113.1314) 
(list 1354.585 113.3084) 
(list 1280.5625 113.3584)))
(apply 'command (append '("pline") coords '("c")))
(setq currobj (ssadd (entlast) currobj))
(setq coords (list 
(list 1280.5625 113.5014) 
(list 1354.585 113.4514) 
(list 1354.585 113.6284) 
(list 1280.5625 113.5784)))
(apply 'command (append '("pline") coords '("c")))
(setq currobj (ssadd (entlast) currobj))
(setq coords (list 
(list 1280.5625 113.7214) 
(list 1354.585 113.7714) 
(list 1354.585 113.9484) 
(list 1280.5625 113.7984)))
(apply 'command (append '("pline") coords '("c")))
(setq currobj (ssadd (entlast) currobj))
(setq coords (list 
(list 1280.5625 113.9414) 
(list 1354.585 114.0914) 
(list 1354.585 114.2684) 
(list 1280.5625 114.0184)))
(apply 'command (append '("pline") coords '("c")))
(setq currobj (ssadd (entlast) currobj))
(setq coords (list 
(list 1280.5625 114.1614) 
(list 1354.585 114.4114) 
(list 1354.585 114.5884) 
(list 1280.5625 114.2384)))
(apply 'command (append '("pline") coords '("c")))
(setq currobj (ssadd (entlast) currobj))
(setq coords (list 
(list 1280.5625 114.3814) 
(list 1354.585 114.7314) 
(list 1354.585 114.9084) 
(list 1280.5625 114.4584)))
(apply 'command (append '("pline") coords '("c")))
(setq currobj (ssadd (entlast) currobj))
(setq coords (list 
(list 1280.5625 114.6014) 
(list 1354.585 115.0514) 
(list 1354.585 115.2284) 
(list 1280.5625 114.6784)))
(apply 'command (append '("pline") coords '("c")))
(setq currobj (ssadd (entlast) currobj))
(setq coords (list 
(list 1280.5625 114.8214) 
(list 1354.585 115.3714) 
(list 1354.585 115.5484) 
(list 1280.5625 114.8984)))
(apply 'command (append '("pline") coords '("c")))
(setq currobj (ssadd (entlast) currobj))
(setq coords (list 
(list 1280.5625 115.0414) 
(list 1354.585 115.6914) 
(list 1354.585 115.8684) 
(list 1280.5625 115.1184)))
(apply 'command (append '("pline") coords '("c")))
(setq currobj (ssadd (entlast) currobj))
(setq coords (list 
(list 1279.4375 115.1184) 
(list 1205.415 115.8684) 
(list 1205.415 115.6914) 
(list 1279.4375 115.0414)))
(apply 'command (append '("pline") coords '("c")))
(setq currobj (ssadd (entlast) currobj))
(setq coords (list 
(list 1279.4375 114.8984) 
(list 1205.415 115.5484) 
(list 1205.415 115.3714) 
(list 1279.4375 114.8214)))
(apply 'command (append '("pline") coords '("c")))
(setq currobj (ssadd (entlast) currobj))
(setq coords (list 
(list 1279.4375 114.6784) 
(list 1205.415 115.2284) 
(list 1205.415 115.0514) 
(list 1279.4375 114.6014)))
(apply 'command (append '("pline") coords '("c")))
(setq currobj (ssadd (entlast) currobj))
(setq coords (list 
(list 1279.4375 114.4584) 
(list 1205.415 114.9084) 
(list 1205.415 114.7314) 
(list 1279.4375 114.3814)))
(apply 'command (append '("pline") coords '("c")))
(setq currobj (ssadd (entlast) currobj))
(setq coords (list 
(list 1279.4375 114.2384) 
(list 1205.415 114.5884) 
(list 1205.415 114.4114) 
(list 1279.4375 114.1614)))
(apply 'command (append '("pline") coords '("c")))
(setq currobj (ssadd (entlast) currobj))
(setq coords (list 
(list 1279.4375 114.0184) 
(list 1205.415 114.2684) 
(list 1205.415 114.0914) 
(list 1279.4375 113.9414)))
(apply 'command (append '("pline") coords '("c")))
(setq currobj (ssadd (entlast) currobj))
(setq coords (list 
(list 1279.4375 113.7984) 
(list 1205.415 113.9484) 
(list 1205.415 113.7714) 
(list 1279.4375 113.7214)))
(apply 'command (append '("pline") coords '("c")))
(setq currobj (ssadd (entlast) currobj))
(setq coords (list 
(list 1279.4375 113.5784) 
(list 1205.415 113.6284) 
(list 1205.415 113.4514) 
(list 1279.4375 113.5014)))
(apply 'command (append '("pline") coords '("c")))
(setq currobj (ssadd (entlast) currobj))
(setq coords (list 
(list 1279.4375 113.3584) 
(list 1205.415 113.3084) 
(list 1205.415 113.1314) 
(list 1279.4375 113.2814)))
(apply 'command (append '("pline") coords '("c")))
(setq currobj (ssadd (entlast) currobj))
(setq coords (list 
(list 1279.4375 113.1384) 
(list 1205.415 112.9884) 
(list 1205.415 112.8114) 
(list 1279.4375 113.0614)))
(apply 'command (append '("pline") coords '("c")))
(setq currobj (ssadd (entlast) currobj))
(setq coords (list 
(list 1279.4375 112.9184) 
(list 1205.415 112.6684) 
(list 1205.415 112.4914) 
(list 1279.4375 112.8414)))
(apply 'command (append '("pline") coords '("c")))
(setq currobj (ssadd (entlast) currobj))
(setq coords (list 
(list 1279.4375 112.6984) 
(list 1205.415 112.3484) 
(list 1205.415 112.1714) 
(list 1279.4375 112.6214)))
(apply 'command (append '("pline") coords '("c")))
(setq currobj (ssadd (entlast) currobj))
(setq coords (list 
(list 1279.4375 112.4784) 
(list 1205.415 112.0284) 
(list 1205.415 111.8514) 
(list 1279.4375 112.4014)))
(apply 'command (append '("pline") coords '("c")))
(setq currobj (ssadd (entlast) currobj))
(setq coords (list 
(list 1279.4375 112.2584) 
(list 1205.415 111.7084) 
(list 1205.415 111.5314) 
(list 1279.4375 112.1814)))
(apply 'command (append '("pline") coords '("c")))
(setq currobj (ssadd (entlast) currobj))
(setq coords (list 
(list 1279.4375 112.0384) 
(list 1205.415 111.3884) 
(list 1205.415 111.2114) 
(list 1279.4375 111.9614)))
(apply 'command (append '("pline") coords '("c")))
(setq currobj (ssadd (entlast) currobj))
(command "_layer" "set" "nitride" "")
(command "_layer" "set" "text" "")
(command "_circle" "1279.0625,100.8184" "0.075")
(command "_circle" "1279.0625,101.1184" "0.075")
(command "_circle" "1279.0625,101.4184" "0.075")
(command "_circle" "1279.0625,101.7184" "0.075")
(command "_circle" "1279.0625,102.0184" "0.075")
(command "_circle" "1278.7625,100.8184" "0.075")
(command "_circle" "1278.7625,101.1184" "0.075")
(command "_circle" "1278.7625,101.4184" "0.075")
(command "_circle" "1278.7625,101.7184" "0.075")
(command "_circle" "1278.7625,102.0184" "0.075")
(command "_circle" "1278.4625,100.8184" "0.075")
(command "_circle" "1278.4625,101.1184" "0.075")
(command "_circle" "1278.4625,101.4184" "0.075")
(command "_circle" "1278.4625,101.7184" "0.075")
(command "_circle" "1278.4625,102.0184" "0.075")
(command "_circle" "1278.1625,100.8184" "0.075")
(command "_circle" "1278.1625,101.1184" "0.075")
(command "_circle" "1278.1625,101.4184" "0.075")
(command "_circle" "1278.1625,101.7184" "0.075")
(command "_circle" "1278.1625,102.0184" "0.075")
(command "_circle" "1277.8625,100.8184" "0.075")
(command "_circle" "1277.8625,101.1184" "0.075")
(command "_circle" "1277.8625,101.4184" "0.075")
(command "_circle" "1277.8625,101.7184" "0.075")
(command "_circle" "1277.8625,102.0184" "0.075")
(command "_layer" "set" "nitride" "")
(setq coords (list 
(list 1280.2625 126.2614) 
(list 1280.2625 241.9061) 
(list 1279.7375 241.9061) 
(list 1279.7375 126.2614)))
(apply 'command (append '("pline") coords '("c")))
(setq currobj (ssadd (entlast) currobj))
(command "_layer" "set" "prebias" "")
(command "_rectangle" "1279.7375,126.2614" "1280.2625,241.9061")
(setq currobj (ssadd (entlast) currobj))
(command "_layer" "set" "nitride" "")
(setq coords (list 
(list 1280.2625 241.9061) 
(list 1280.5625 251.9061) 
(list 1280.5625 251.9061) 
(list 1280.5625 252.9061) 
(list 1354.585 252.1561) 
(list 1354.585 257.0991) 
(list 1280.5625 256.3491) 
(list 1280.5625 257.3491) 
(list 1280.5625 257.3491) 
(list 1280.2625 267.3491) 
(list 1279.7375 267.3491) 
(list 1279.4375 257.3491) 
(list 1279.4375 257.3491) 
(list 1279.4375 256.3491) 
(list 1205.415 257.0991) 
(list 1205.415 252.1561) 
(list 1279.4375 252.9061) 
(list 1279.4375 251.9061) 
(list 1279.4375 251.9061) 
(list 1279.7375 241.9061)))
(apply 'command (append '("pline") coords '("c")))
(setq currobj (ssadd (entlast) currobj))
(command "_layer" "set" "prebias" "")
(setq coords (list 
(list 1279.4375 241.9061) 
(list 1279.4375 252.9061) 
(list 1205.415 252.1561) 
(list 1205.415 257.0991) 
(list 1279.4375 256.3491) 
(list 1279.4375 267.3491) 
(list 1280.5625 267.3491) 
(list 1280.5625 256.3491) 
(list 1354.585 257.0991) 
(list 1354.585 252.1561) 
(list 1280.5625 252.9061) 
(list 1280.5625 241.9061)))
(apply 'command (append '("pline") coords '("c")))
(setq currobj (ssadd (entlast) currobj))
(command "_layer" "set" "nitride" "")
(command "_layer" "set" "fda1" "")
(setq coords (list 
(list 1280.5625 253.0491) 
(list 1354.585 252.2991) 
(list 1354.585 252.4761) 
(list 1280.5625 253.1261)))
(apply 'command (append '("pline") coords '("c")))
(setq currobj (ssadd (entlast) currobj))
(setq coords (list 
(list 1280.5625 253.2691) 
(list 1354.585 252.6191) 
(list 1354.585 252.7961) 
(list 1280.5625 253.3461)))
(apply 'command (append '("pline") coords '("c")))
(setq currobj (ssadd (entlast) currobj))
(setq coords (list 
(list 1280.5625 253.4891) 
(list 1354.585 252.9391) 
(list 1354.585 253.1161) 
(list 1280.5625 253.5661)))
(apply 'command (append '("pline") coords '("c")))
(setq currobj (ssadd (entlast) currobj))
(setq coords (list 
(list 1280.5625 253.7091) 
(list 1354.585 253.2591) 
(list 1354.585 253.4361) 
(list 1280.5625 253.7861)))
(apply 'command (append '("pline") coords '("c")))
(setq currobj (ssadd (entlast) currobj))
(setq coords (list 
(list 1280.5625 253.9291) 
(list 1354.585 253.5791) 
(list 1354.585 253.7561) 
(list 1280.5625 254.0061)))
(apply 'command (append '("pline") coords '("c")))
(setq currobj (ssadd (entlast) currobj))
(setq coords (list 
(list 1280.5625 254.1491) 
(list 1354.585 253.8991) 
(list 1354.585 254.0761) 
(list 1280.5625 254.2261)))
(apply 'command (append '("pline") coords '("c")))
(setq currobj (ssadd (entlast) currobj))
(setq coords (list 
(list 1280.5625 254.3691) 
(list 1354.585 254.2191) 
(list 1354.585 254.3961) 
(list 1280.5625 254.4461)))
(apply 'command (append '("pline") coords '("c")))
(setq currobj (ssadd (entlast) currobj))
(setq coords (list 
(list 1280.5625 254.5891) 
(list 1354.585 254.5391) 
(list 1354.585 254.7161) 
(list 1280.5625 254.6661)))
(apply 'command (append '("pline") coords '("c")))
(setq currobj (ssadd (entlast) currobj))
(setq coords (list 
(list 1280.5625 254.8091) 
(list 1354.585 254.8591) 
(list 1354.585 255.0361) 
(list 1280.5625 254.8861)))
(apply 'command (append '("pline") coords '("c")))
(setq currobj (ssadd (entlast) currobj))
(setq coords (list 
(list 1280.5625 255.0291) 
(list 1354.585 255.1791) 
(list 1354.585 255.3561) 
(list 1280.5625 255.1061)))
(apply 'command (append '("pline") coords '("c")))
(setq currobj (ssadd (entlast) currobj))
(setq coords (list 
(list 1280.5625 255.2491) 
(list 1354.585 255.4991) 
(list 1354.585 255.6761) 
(list 1280.5625 255.3261)))
(apply 'command (append '("pline") coords '("c")))
(setq currobj (ssadd (entlast) currobj))
(setq coords (list 
(list 1280.5625 255.4691) 
(list 1354.585 255.8191) 
(list 1354.585 255.9961) 
(list 1280.5625 255.5461)))
(apply 'command (append '("pline") coords '("c")))
(setq currobj (ssadd (entlast) currobj))
(setq coords (list 
(list 1280.5625 255.6891) 
(list 1354.585 256.1391) 
(list 1354.585 256.3161) 
(list 1280.5625 255.7661)))
(apply 'command (append '("pline") coords '("c")))
(setq currobj (ssadd (entlast) currobj))
(setq coords (list 
(list 1280.5625 255.9091) 
(list 1354.585 256.4591) 
(list 1354.585 256.6361) 
(list 1280.5625 255.9861)))
(apply 'command (append '("pline") coords '("c")))
(setq currobj (ssadd (entlast) currobj))
(setq coords (list 
(list 1280.5625 256.1291) 
(list 1354.585 256.7791) 
(list 1354.585 256.9561) 
(list 1280.5625 256.2061)))
(apply 'command (append '("pline") coords '("c")))
(setq currobj (ssadd (entlast) currobj))
(setq coords (list 
(list 1279.4375 256.2061) 
(list 1205.415 256.9561) 
(list 1205.415 256.7791) 
(list 1279.4375 256.1291)))
(apply 'command (append '("pline") coords '("c")))
(setq currobj (ssadd (entlast) currobj))
(setq coords (list 
(list 1279.4375 255.9861) 
(list 1205.415 256.6361) 
(list 1205.415 256.4591) 
(list 1279.4375 255.9091)))
(apply 'command (append '("pline") coords '("c")))
(setq currobj (ssadd (entlast) currobj))
(setq coords (list 
(list 1279.4375 255.7661) 
(list 1205.415 256.3161) 
(list 1205.415 256.1391) 
(list 1279.4375 255.6891)))
(apply 'command (append '("pline") coords '("c")))
(setq currobj (ssadd (entlast) currobj))
(setq coords (list 
(list 1279.4375 255.5461) 
(list 1205.415 255.9961) 
(list 1205.415 255.8191) 
(list 1279.4375 255.4691)))
(apply 'command (append '("pline") coords '("c")))
(setq currobj (ssadd (entlast) currobj))
(setq coords (list 
(list 1279.4375 255.3261) 
(list 1205.415 255.6761) 
(list 1205.415 255.4991) 
(list 1279.4375 255.2491)))
(apply 'command (append '("pline") coords '("c")))
(setq currobj (ssadd (entlast) currobj))
(setq coords (list 
(list 1279.4375 255.1061) 
(list 1205.415 255.3561) 
(list 1205.415 255.1791) 
(list 1279.4375 255.0291)))
(apply 'command (append '("pline") coords '("c")))
(setq currobj (ssadd (entlast) currobj))
(setq coords (list 
(list 1279.4375 254.8861) 
(list 1205.415 255.0361) 
(list 1205.415 254.8591) 
(list 1279.4375 254.8091)))
(apply 'command (append '("pline") coords '("c")))
(setq currobj (ssadd (entlast) currobj))
(setq coords (list 
(list 1279.4375 254.6661) 
(list 1205.415 254.7161) 
(list 1205.415 254.5391) 
(list 1279.4375 254.5891)))
(apply 'command (append '("pline") coords '("c")))
(setq currobj (ssadd (entlast) currobj))
(setq coords (list 
(list 1279.4375 254.4461) 
(list 1205.415 254.3961) 
(list 1205.415 254.2191) 
(list 1279.4375 254.3691)))
(apply 'command (append '("pline") coords '("c")))
(setq currobj (ssadd (entlast) currobj))
(setq coords (list 
(list 1279.4375 254.2261) 
(list 1205.415 254.0761) 
(list 1205.415 253.8991) 
(list 1279.4375 254.1491)))
(apply 'command (append '("pline") coords '("c")))
(setq currobj (ssadd (entlast) currobj))
(setq coords (list 
(list 1279.4375 254.0061) 
(list 1205.415 253.7561) 
(list 1205.415 253.5791) 
(list 1279.4375 253.9291)))
(apply 'command (append '("pline") coords '("c")))
(setq currobj (ssadd (entlast) currobj))
(setq coords (list 
(list 1279.4375 253.7861) 
(list 1205.415 253.4361) 
(list 1205.415 253.2591) 
(list 1279.4375 253.7091)))
(apply 'command (append '("pline") coords '("c")))
(setq currobj (ssadd (entlast) currobj))
(setq coords (list 
(list 1279.4375 253.5661) 
(list 1205.415 253.1161) 
(list 1205.415 252.9391) 
(list 1279.4375 253.4891)))
(apply 'command (append '("pline") coords '("c")))
(setq currobj (ssadd (entlast) currobj))
(setq coords (list 
(list 1279.4375 253.3461) 
(list 1205.415 252.7961) 
(list 1205.415 252.6191) 
(list 1279.4375 253.2691)))
(apply 'command (append '("pline") coords '("c")))
(setq currobj (ssadd (entlast) currobj))
(setq coords (list 
(list 1279.4375 253.1261) 
(list 1205.415 252.4761) 
(list 1205.415 252.2991) 
(list 1279.4375 253.0491)))
(apply 'command (append '("pline") coords '("c")))
(setq currobj (ssadd (entlast) currobj))
(command "_layer" "set" "nitride" "")
(command "_layer" "set" "text" "")
(command "_circle" "1279.0625,241.9061" "0.075")
(command "_circle" "1279.0625,242.2061" "0.075")
(command "_circle" "1279.0625,242.5061" "0.075")
(command "_circle" "1279.0625,242.8061" "0.075")
(command "_circle" "1279.0625,243.1061" "0.075")
(command "_circle" "1278.7625,241.9061" "0.075")
(command "_circle" "1278.7625,242.2061" "0.075")
(command "_circle" "1278.7625,242.5061" "0.075")
(command "_circle" "1278.7625,242.8061" "0.075")
(command "_circle" "1278.7625,243.1061" "0.075")
(command "_circle" "1278.4625,241.9061" "0.075")
(command "_circle" "1278.4625,242.2061" "0.075")
(command "_circle" "1278.4625,242.5061" "0.075")
(command "_circle" "1278.4625,242.8061" "0.075")
(command "_circle" "1278.4625,243.1061" "0.075")
(command "_circle" "1278.1625,241.9061" "0.075")
(command "_circle" "1278.1625,242.2061" "0.075")
(command "_circle" "1278.1625,242.5061" "0.075")
(command "_circle" "1278.1625,242.8061" "0.075")
(command "_circle" "1278.1625,243.1061" "0.075")
(command "_circle" "1277.8625,241.9061" "0.075")
(command "_circle" "1277.8625,242.2061" "0.075")
(command "_circle" "1277.8625,242.5061" "0.075")
(command "_circle" "1277.8625,242.8061" "0.075")
(command "_circle" "1277.8625,243.1061" "0.075")
(command "_layer" "set" "nitride" "")
(setq coords (list 
(list 1280.2625 267.3491) 
(list 1280.2625 382.9939) 
(list 1279.7375 382.9939) 
(list 1279.7375 267.3491)))
(apply 'command (append '("pline") coords '("c")))
(setq currobj (ssadd (entlast) currobj))
(command "_layer" "set" "prebias" "")
(command "_rectangle" "1279.7375,267.3491" "1280.2625,382.9939")
(setq currobj (ssadd (entlast) currobj))
(command "_layer" "set" "nitride" "")
(setq coords (list 
(list 1280.2625 382.9939) 
(list 1280.5625 392.9939) 
(list 1280.5625 392.9939) 
(list 1280.5625 393.9939) 
(list 1354.585 393.2439) 
(list 1354.585 398.1869) 
(list 1280.5625 397.4369) 
(list 1280.5625 398.4369) 
(list 1280.5625 398.4369) 
(list 1280.2625 408.4369) 
(list 1279.7375 408.4369) 
(list 1279.4375 398.4369) 
(list 1279.4375 398.4369) 
(list 1279.4375 397.4369) 
(list 1205.415 398.1869) 
(list 1205.415 393.2439) 
(list 1279.4375 393.9939) 
(list 1279.4375 392.9939) 
(list 1279.4375 392.9939) 
(list 1279.7375 382.9939)))
(apply 'command (append '("pline") coords '("c")))
(setq currobj (ssadd (entlast) currobj))
(command "_layer" "set" "prebias" "")
(setq coords (list 
(list 1279.4375 382.9939) 
(list 1279.4375 393.9939) 
(list 1205.415 393.2439) 
(list 1205.415 398.1869) 
(list 1279.4375 397.4369) 
(list 1279.4375 408.4369) 
(list 1280.5625 408.4369) 
(list 1280.5625 397.4369) 
(list 1354.585 398.1869) 
(list 1354.585 393.2439) 
(list 1280.5625 393.9939) 
(list 1280.5625 382.9939)))
(apply 'command (append '("pline") coords '("c")))
(setq currobj (ssadd (entlast) currobj))
(command "_layer" "set" "nitride" "")
(command "_layer" "set" "fda1" "")
(setq coords (list 
(list 1280.5625 394.1369) 
(list 1354.585 393.3869) 
(list 1354.585 393.5639) 
(list 1280.5625 394.2139)))
(apply 'command (append '("pline") coords '("c")))
(setq currobj (ssadd (entlast) currobj))
(setq coords (list 
(list 1280.5625 394.3569) 
(list 1354.585 393.7069) 
(list 1354.585 393.8839) 
(list 1280.5625 394.4339)))
(apply 'command (append '("pline") coords '("c")))
(setq currobj (ssadd (entlast) currobj))
(setq coords (list 
(list 1280.5625 394.5769) 
(list 1354.585 394.0269) 
(list 1354.585 394.2039) 
(list 1280.5625 394.6539)))
(apply 'command (append '("pline") coords '("c")))
(setq currobj (ssadd (entlast) currobj))
(setq coords (list 
(list 1280.5625 394.7969) 
(list 1354.585 394.3469) 
(list 1354.585 394.5239) 
(list 1280.5625 394.8739)))
(apply 'command (append '("pline") coords '("c")))
(setq currobj (ssadd (entlast) currobj))
(setq coords (list 
(list 1280.5625 395.0169) 
(list 1354.585 394.6669) 
(list 1354.585 394.8439) 
(list 1280.5625 395.0939)))
(apply 'command (append '("pline") coords '("c")))
(setq currobj (ssadd (entlast) currobj))
(setq coords (list 
(list 1280.5625 395.2369) 
(list 1354.585 394.9869) 
(list 1354.585 395.1639) 
(list 1280.5625 395.3139)))
(apply 'command (append '("pline") coords '("c")))
(setq currobj (ssadd (entlast) currobj))
(setq coords (list 
(list 1280.5625 395.4569) 
(list 1354.585 395.3069) 
(list 1354.585 395.4839) 
(list 1280.5625 395.5339)))
(apply 'command (append '("pline") coords '("c")))
(setq currobj (ssadd (entlast) currobj))
(setq coords (list 
(list 1280.5625 395.6769) 
(list 1354.585 395.6269) 
(list 1354.585 395.8039) 
(list 1280.5625 395.7539)))
(apply 'command (append '("pline") coords '("c")))
(setq currobj (ssadd (entlast) currobj))
(setq coords (list 
(list 1280.5625 395.8969) 
(list 1354.585 395.9469) 
(list 1354.585 396.1239) 
(list 1280.5625 395.9739)))
(apply 'command (append '("pline") coords '("c")))
(setq currobj (ssadd (entlast) currobj))
(setq coords (list 
(list 1280.5625 396.1169) 
(list 1354.585 396.2669) 
(list 1354.585 396.4439) 
(list 1280.5625 396.1939)))
(apply 'command (append '("pline") coords '("c")))
(setq currobj (ssadd (entlast) currobj))
(setq coords (list 
(list 1280.5625 396.3369) 
(list 1354.585 396.5869) 
(list 1354.585 396.7639) 
(list 1280.5625 396.4139)))
(apply 'command (append '("pline") coords '("c")))
(setq currobj (ssadd (entlast) currobj))
(setq coords (list 
(list 1280.5625 396.5569) 
(list 1354.585 396.9069) 
(list 1354.585 397.0839) 
(list 1280.5625 396.6339)))
(apply 'command (append '("pline") coords '("c")))
(setq currobj (ssadd (entlast) currobj))
(setq coords (list 
(list 1280.5625 396.7769) 
(list 1354.585 397.2269) 
(list 1354.585 397.4039) 
(list 1280.5625 396.8539)))
(apply 'command (append '("pline") coords '("c")))
(setq currobj (ssadd (entlast) currobj))
(setq coords (list 
(list 1280.5625 396.9969) 
(list 1354.585 397.5469) 
(list 1354.585 397.7239) 
(list 1280.5625 397.0739)))
(apply 'command (append '("pline") coords '("c")))
(setq currobj (ssadd (entlast) currobj))
(setq coords (list 
(list 1280.5625 397.2169) 
(list 1354.585 397.8669) 
(list 1354.585 398.0439) 
(list 1280.5625 397.2939)))
(apply 'command (append '("pline") coords '("c")))
(setq currobj (ssadd (entlast) currobj))
(setq coords (list 
(list 1279.4375 397.2939) 
(list 1205.415 398.0439) 
(list 1205.415 397.8669) 
(list 1279.4375 397.2169)))
(apply 'command (append '("pline") coords '("c")))
(setq currobj (ssadd (entlast) currobj))
(setq coords (list 
(list 1279.4375 397.0739) 
(list 1205.415 397.7239) 
(list 1205.415 397.5469) 
(list 1279.4375 396.9969)))
(apply 'command (append '("pline") coords '("c")))
(setq currobj (ssadd (entlast) currobj))
(setq coords (list 
(list 1279.4375 396.8539) 
(list 1205.415 397.4039) 
(list 1205.415 397.2269) 
(list 1279.4375 396.7769)))
(apply 'command (append '("pline") coords '("c")))
(setq currobj (ssadd (entlast) currobj))
(setq coords (list 
(list 1279.4375 396.6339) 
(list 1205.415 397.0839) 
(list 1205.415 396.9069) 
(list 1279.4375 396.5569)))
(apply 'command (append '("pline") coords '("c")))
(setq currobj (ssadd (entlast) currobj))
(setq coords (list 
(list 1279.4375 396.4139) 
(list 1205.415 396.7639) 
(list 1205.415 396.5869) 
(list 1279.4375 396.3369)))
(apply 'command (append '("pline") coords '("c")))
(setq currobj (ssadd (entlast) currobj))
(setq coords (list 
(list 1279.4375 396.1939) 
(list 1205.415 396.4439) 
(list 1205.415 396.2669) 
(list 1279.4375 396.1169)))
(apply 'command (append '("pline") coords '("c")))
(setq currobj (ssadd (entlast) currobj))
(setq coords (list 
(list 1279.4375 395.9739) 
(list 1205.415 396.1239) 
(list 1205.415 395.9469) 
(list 1279.4375 395.8969)))
(apply 'command (append '("pline") coords '("c")))
(setq currobj (ssadd (entlast) currobj))
(setq coords (list 
(list 1279.4375 395.7539) 
(list 1205.415 395.8039) 
(list 1205.415 395.6269) 
(list 1279.4375 395.6769)))
(apply 'command (append '("pline") coords '("c")))
(setq currobj (ssadd (entlast) currobj))
(setq coords (list 
(list 1279.4375 395.5339) 
(list 1205.415 395.4839) 
(list 1205.415 395.3069) 
(list 1279.4375 395.4569)))
(apply 'command (append '("pline") coords '("c")))
(setq currobj (ssadd (entlast) currobj))
(setq coords (list 
(list 1279.4375 395.3139) 
(list 1205.415 395.1639) 
(list 1205.415 394.9869) 
(list 1279.4375 395.2369)))
(apply 'command (append '("pline") coords '("c")))
(setq currobj (ssadd (entlast) currobj))
(setq coords (list 
(list 1279.4375 395.0939) 
(list 1205.415 394.8439) 
(list 1205.415 394.6669) 
(list 1279.4375 395.0169)))
(apply 'command (append '("pline") coords '("c")))
(setq currobj (ssadd (entlast) currobj))
(setq coords (list 
(list 1279.4375 394.8739) 
(list 1205.415 394.5239) 
(list 1205.415 394.3469) 
(list 1279.4375 394.7969)))
(apply 'command (append '("pline") coords '("c")))
(setq currobj (ssadd (entlast) currobj))
(setq coords (list 
(list 1279.4375 394.6539) 
(list 1205.415 394.2039) 
(list 1205.415 394.0269) 
(list 1279.4375 394.5769)))
(apply 'command (append '("pline") coords '("c")))
(setq currobj (ssadd (entlast) currobj))
(setq coords (list 
(list 1279.4375 394.4339) 
(list 1205.415 393.8839) 
(list 1205.415 393.7069) 
(list 1279.4375 394.3569)))
(apply 'command (append '("pline") coords '("c")))
(setq currobj (ssadd (entlast) currobj))
(setq coords (list 
(list 1279.4375 394.2139) 
(list 1205.415 393.5639) 
(list 1205.415 393.3869) 
(list 1279.4375 394.1369)))
(apply 'command (append '("pline") coords '("c")))
(setq currobj (ssadd (entlast) currobj))
(command "_layer" "set" "nitride" "")
(command "_layer" "set" "text" "")
(command "_circle" "1279.0625,382.9939" "0.075")
(command "_circle" "1279.0625,383.2939" "0.075")
(command "_circle" "1279.0625,383.5939" "0.075")
(command "_circle" "1279.0625,383.8939" "0.075")
(command "_circle" "1279.0625,384.1939" "0.075")
(command "_circle" "1278.7625,382.9939" "0.075")
(command "_circle" "1278.7625,383.2939" "0.075")
(command "_circle" "1278.7625,383.5939" "0.075")
(command "_circle" "1278.7625,383.8939" "0.075")
(command "_circle" "1278.7625,384.1939" "0.075")
(command "_circle" "1278.4625,382.9939" "0.075")
(command "_circle" "1278.4625,383.2939" "0.075")
(command "_circle" "1278.4625,383.5939" "0.075")
(command "_circle" "1278.4625,383.8939" "0.075")
(command "_circle" "1278.4625,384.1939" "0.075")
(command "_circle" "1278.1625,382.9939" "0.075")
(command "_circle" "1278.1625,383.2939" "0.075")
(command "_circle" "1278.1625,383.5939" "0.075")
(command "_circle" "1278.1625,383.8939" "0.075")
(command "_circle" "1278.1625,384.1939" "0.075")
(command "_circle" "1277.8625,382.9939" "0.075")
(command "_circle" "1277.8625,383.2939" "0.075")
(command "_circle" "1277.8625,383.5939" "0.075")
(command "_circle" "1277.8625,383.8939" "0.075")
(command "_circle" "1277.8625,384.1939" "0.075")
(command "_layer" "set" "nitride" "")
(setq coords (list 
(list 1280.2625 408.4369) 
(list 1280.2625 524.0816) 
(list 1279.7375 524.0816) 
(list 1279.7375 408.4369)))
(apply 'command (append '("pline") coords '("c")))
(setq currobj (ssadd (entlast) currobj))
(command "_layer" "set" "prebias" "")
(command "_rectangle" "1279.7375,408.4369" "1280.2625,524.0816")
(setq currobj (ssadd (entlast) currobj))
(command "_layer" "set" "nitride" "")
(setq coords (list 
(list 1280.2625 524.0816) 
(list 1280.5625 534.0816) 
(list 1280.5625 534.0816) 
(list 1280.5625 535.0816) 
(list 1354.585 534.3316) 
(list 1354.585 539.2746) 
(list 1280.5625 538.5246) 
(list 1280.5625 539.5246) 
(list 1280.5625 539.5246) 
(list 1280.2625 549.5246) 
(list 1279.7375 549.5246) 
(list 1279.4375 539.5246) 
(list 1279.4375 539.5246) 
(list 1279.4375 538.5246) 
(list 1205.415 539.2746) 
(list 1205.415 534.3316) 
(list 1279.4375 535.0816) 
(list 1279.4375 534.0816) 
(list 1279.4375 534.0816) 
(list 1279.7375 524.0816)))
(apply 'command (append '("pline") coords '("c")))
(setq currobj (ssadd (entlast) currobj))
(command "_layer" "set" "prebias" "")
(setq coords (list 
(list 1279.4375 524.0816) 
(list 1279.4375 535.0816) 
(list 1205.415 534.3316) 
(list 1205.415 539.2746) 
(list 1279.4375 538.5246) 
(list 1279.4375 549.5246) 
(list 1280.5625 549.5246) 
(list 1280.5625 538.5246) 
(list 1354.585 539.2746) 
(list 1354.585 534.3316) 
(list 1280.5625 535.0816) 
(list 1280.5625 524.0816)))
(apply 'command (append '("pline") coords '("c")))
(setq currobj (ssadd (entlast) currobj))
(command "_layer" "set" "nitride" "")
(command "_layer" "set" "fda1" "")
(setq coords (list 
(list 1280.5625 535.2246) 
(list 1354.585 534.4746) 
(list 1354.585 534.6516) 
(list 1280.5625 535.3016)))
(apply 'command (append '("pline") coords '("c")))
(setq currobj (ssadd (entlast) currobj))
(setq coords (list 
(list 1280.5625 535.4446) 
(list 1354.585 534.7946) 
(list 1354.585 534.9716) 
(list 1280.5625 535.5216)))
(apply 'command (append '("pline") coords '("c")))
(setq currobj (ssadd (entlast) currobj))
(setq coords (list 
(list 1280.5625 535.6646) 
(list 1354.585 535.1146) 
(list 1354.585 535.2916) 
(list 1280.5625 535.7416)))
(apply 'command (append '("pline") coords '("c")))
(setq currobj (ssadd (entlast) currobj))
(setq coords (list 
(list 1280.5625 535.8846) 
(list 1354.585 535.4346) 
(list 1354.585 535.6116) 
(list 1280.5625 535.9616)))
(apply 'command (append '("pline") coords '("c")))
(setq currobj (ssadd (entlast) currobj))
(setq coords (list 
(list 1280.5625 536.1046) 
(list 1354.585 535.7546) 
(list 1354.585 535.9316) 
(list 1280.5625 536.1816)))
(apply 'command (append '("pline") coords '("c")))
(setq currobj (ssadd (entlast) currobj))
(setq coords (list 
(list 1280.5625 536.3246) 
(list 1354.585 536.0746) 
(list 1354.585 536.2516) 
(list 1280.5625 536.4016)))
(apply 'command (append '("pline") coords '("c")))
(setq currobj (ssadd (entlast) currobj))
(setq coords (list 
(list 1280.5625 536.5446) 
(list 1354.585 536.3946) 
(list 1354.585 536.5716) 
(list 1280.5625 536.6216)))
(apply 'command (append '("pline") coords '("c")))
(setq currobj (ssadd (entlast) currobj))
(setq coords (list 
(list 1280.5625 536.7646) 
(list 1354.585 536.7146) 
(list 1354.585 536.8916) 
(list 1280.5625 536.8416)))
(apply 'command (append '("pline") coords '("c")))
(setq currobj (ssadd (entlast) currobj))
(setq coords (list 
(list 1280.5625 536.9846) 
(list 1354.585 537.0346) 
(list 1354.585 537.2116) 
(list 1280.5625 537.0616)))
(apply 'command (append '("pline") coords '("c")))
(setq currobj (ssadd (entlast) currobj))
(setq coords (list 
(list 1280.5625 537.2046) 
(list 1354.585 537.3546) 
(list 1354.585 537.5316) 
(list 1280.5625 537.2816)))
(apply 'command (append '("pline") coords '("c")))
(setq currobj (ssadd (entlast) currobj))
(setq coords (list 
(list 1280.5625 537.4246) 
(list 1354.585 537.6746) 
(list 1354.585 537.8516) 
(list 1280.5625 537.5016)))
(apply 'command (append '("pline") coords '("c")))
(setq currobj (ssadd (entlast) currobj))
(setq coords (list 
(list 1280.5625 537.6446) 
(list 1354.585 537.9946) 
(list 1354.585 538.1716) 
(list 1280.5625 537.7216)))
(apply 'command (append '("pline") coords '("c")))
(setq currobj (ssadd (entlast) currobj))
(setq coords (list 
(list 1280.5625 537.8646) 
(list 1354.585 538.3146) 
(list 1354.585 538.4916) 
(list 1280.5625 537.9416)))
(apply 'command (append '("pline") coords '("c")))
(setq currobj (ssadd (entlast) currobj))
(setq coords (list 
(list 1280.5625 538.0846) 
(list 1354.585 538.6346) 
(list 1354.585 538.8116) 
(list 1280.5625 538.1616)))
(apply 'command (append '("pline") coords '("c")))
(setq currobj (ssadd (entlast) currobj))
(setq coords (list 
(list 1280.5625 538.3046) 
(list 1354.585 538.9546) 
(list 1354.585 539.1316) 
(list 1280.5625 538.3816)))
(apply 'command (append '("pline") coords '("c")))
(setq currobj (ssadd (entlast) currobj))
(setq coords (list 
(list 1279.4375 538.3816) 
(list 1205.415 539.1316) 
(list 1205.415 538.9546) 
(list 1279.4375 538.3046)))
(apply 'command (append '("pline") coords '("c")))
(setq currobj (ssadd (entlast) currobj))
(setq coords (list 
(list 1279.4375 538.1616) 
(list 1205.415 538.8116) 
(list 1205.415 538.6346) 
(list 1279.4375 538.0846)))
(apply 'command (append '("pline") coords '("c")))
(setq currobj (ssadd (entlast) currobj))
(setq coords (list 
(list 1279.4375 537.9416) 
(list 1205.415 538.4916) 
(list 1205.415 538.3146) 
(list 1279.4375 537.8646)))
(apply 'command (append '("pline") coords '("c")))
(setq currobj (ssadd (entlast) currobj))
(setq coords (list 
(list 1279.4375 537.7216) 
(list 1205.415 538.1716) 
(list 1205.415 537.9946) 
(list 1279.4375 537.6446)))
(apply 'command (append '("pline") coords '("c")))
(setq currobj (ssadd (entlast) currobj))
(setq coords (list 
(list 1279.4375 537.5016) 
(list 1205.415 537.8516) 
(list 1205.415 537.6746) 
(list 1279.4375 537.4246)))
(apply 'command (append '("pline") coords '("c")))
(setq currobj (ssadd (entlast) currobj))
(setq coords (list 
(list 1279.4375 537.2816) 
(list 1205.415 537.5316) 
(list 1205.415 537.3546) 
(list 1279.4375 537.2046)))
(apply 'command (append '("pline") coords '("c")))
(setq currobj (ssadd (entlast) currobj))
(setq coords (list 
(list 1279.4375 537.0616) 
(list 1205.415 537.2116) 
(list 1205.415 537.0346) 
(list 1279.4375 536.9846)))
(apply 'command (append '("pline") coords '("c")))
(setq currobj (ssadd (entlast) currobj))
(setq coords (list 
(list 1279.4375 536.8416) 
(list 1205.415 536.8916) 
(list 1205.415 536.7146) 
(list 1279.4375 536.7646)))
(apply 'command (append '("pline") coords '("c")))
(setq currobj (ssadd (entlast) currobj))
(setq coords (list 
(list 1279.4375 536.6216) 
(list 1205.415 536.5716) 
(list 1205.415 536.3946) 
(list 1279.4375 536.5446)))
(apply 'command (append '("pline") coords '("c")))
(setq currobj (ssadd (entlast) currobj))
(setq coords (list 
(list 1279.4375 536.4016) 
(list 1205.415 536.2516) 
(list 1205.415 536.0746) 
(list 1279.4375 536.3246)))
(apply 'command (append '("pline") coords '("c")))
(setq currobj (ssadd (entlast) currobj))
(setq coords (list 
(list 1279.4375 536.1816) 
(list 1205.415 535.9316) 
(list 1205.415 535.7546) 
(list 1279.4375 536.1046)))
(apply 'command (append '("pline") coords '("c")))
(setq currobj (ssadd (entlast) currobj))
(setq coords (list 
(list 1279.4375 535.9616) 
(list 1205.415 535.6116) 
(list 1205.415 535.4346) 
(list 1279.4375 535.8846)))
(apply 'command (append '("pline") coords '("c")))
(setq currobj (ssadd (entlast) currobj))
(setq coords (list 
(list 1279.4375 535.7416) 
(list 1205.415 535.2916) 
(list 1205.415 535.1146) 
(list 1279.4375 535.6646)))
(apply 'command (append '("pline") coords '("c")))
(setq currobj (ssadd (entlast) currobj))
(setq coords (list 
(list 1279.4375 535.5216) 
(list 1205.415 534.9716) 
(list 1205.415 534.7946) 
(list 1279.4375 535.4446)))
(apply 'command (append '("pline") coords '("c")))
(setq currobj (ssadd (entlast) currobj))
(setq coords (list 
(list 1279.4375 535.3016) 
(list 1205.415 534.6516) 
(list 1205.415 534.4746) 
(list 1279.4375 535.2246)))
(apply 'command (append '("pline") coords '("c")))
(setq currobj (ssadd (entlast) currobj))
(command "_layer" "set" "nitride" "")
(command "_layer" "set" "text" "")
(command "_circle" "1279.0625,524.0816" "0.075")
(command "_circle" "1279.0625,524.3816" "0.075")
(command "_circle" "1279.0625,524.6816" "0.075")
(command "_circle" "1279.0625,524.9816" "0.075")
(command "_circle" "1279.0625,525.2816" "0.075")
(command "_circle" "1278.7625,524.0816" "0.075")
(command "_circle" "1278.7625,524.3816" "0.075")
(command "_circle" "1278.7625,524.6816" "0.075")
(command "_circle" "1278.7625,524.9816" "0.075")
(command "_circle" "1278.7625,525.2816" "0.075")
(command "_circle" "1278.4625,524.0816" "0.075")
(command "_circle" "1278.4625,524.3816" "0.075")
(command "_circle" "1278.4625,524.6816" "0.075")
(command "_circle" "1278.4625,524.9816" "0.075")
(command "_circle" "1278.4625,525.2816" "0.075")
(command "_circle" "1278.1625,524.0816" "0.075")
(command "_circle" "1278.1625,524.3816" "0.075")
(command "_circle" "1278.1625,524.6816" "0.075")
(command "_circle" "1278.1625,524.9816" "0.075")
(command "_circle" "1278.1625,525.2816" "0.075")
(command "_circle" "1277.8625,524.0816" "0.075")
(command "_circle" "1277.8625,524.3816" "0.075")
(command "_circle" "1277.8625,524.6816" "0.075")
(command "_circle" "1277.8625,524.9816" "0.075")
(command "_circle" "1277.8625,525.2816" "0.075")
(command "_layer" "set" "nitride" "")
(setq coords (list 
(list 1280.2625 549.5246) 
(list 1280.2625 665.1693) 
(list 1279.7375 665.1693) 
(list 1279.7375 549.5246)))
(apply 'command (append '("pline") coords '("c")))
(setq currobj (ssadd (entlast) currobj))
(command "_layer" "set" "prebias" "")
(command "_rectangle" "1279.7375,549.5246" "1280.2625,665.1693")
(setq currobj (ssadd (entlast) currobj))
(command "_layer" "set" "nitride" "")
(setq coords (list 
(list 1280.2625 665.1693) 
(list 1280.5625 675.1693) 
(list 1280.5625 675.1693) 
(list 1280.5625 676.1693) 
(list 1354.585 675.4193) 
(list 1354.585 680.3623) 
(list 1280.5625 679.6123) 
(list 1280.5625 680.6123) 
(list 1280.5625 680.6123) 
(list 1280.2625 690.6123) 
(list 1279.7375 690.6123) 
(list 1279.4375 680.6123) 
(list 1279.4375 680.6123) 
(list 1279.4375 679.6123) 
(list 1205.415 680.3623) 
(list 1205.415 675.4193) 
(list 1279.4375 676.1693) 
(list 1279.4375 675.1693) 
(list 1279.4375 675.1693) 
(list 1279.7375 665.1693)))
(apply 'command (append '("pline") coords '("c")))
(setq currobj (ssadd (entlast) currobj))
(command "_layer" "set" "prebias" "")
(setq coords (list 
(list 1279.4375 665.1693) 
(list 1279.4375 676.1693) 
(list 1205.415 675.4193) 
(list 1205.415 680.3623) 
(list 1279.4375 679.6123) 
(list 1279.4375 690.6123) 
(list 1280.5625 690.6123) 
(list 1280.5625 679.6123) 
(list 1354.585 680.3623) 
(list 1354.585 675.4193) 
(list 1280.5625 676.1693) 
(list 1280.5625 665.1693)))
(apply 'command (append '("pline") coords '("c")))
(setq currobj (ssadd (entlast) currobj))
(command "_layer" "set" "nitride" "")
(command "_layer" "set" "fda1" "")
(setq coords (list 
(list 1280.5625 676.3123) 
(list 1354.585 675.5623) 
(list 1354.585 675.7393) 
(list 1280.5625 676.3893)))
(apply 'command (append '("pline") coords '("c")))
(setq currobj (ssadd (entlast) currobj))
(setq coords (list 
(list 1280.5625 676.5323) 
(list 1354.585 675.8823) 
(list 1354.585 676.0593) 
(list 1280.5625 676.6093)))
(apply 'command (append '("pline") coords '("c")))
(setq currobj (ssadd (entlast) currobj))
(setq coords (list 
(list 1280.5625 676.7523) 
(list 1354.585 676.2023) 
(list 1354.585 676.3793) 
(list 1280.5625 676.8293)))
(apply 'command (append '("pline") coords '("c")))
(setq currobj (ssadd (entlast) currobj))
(setq coords (list 
(list 1280.5625 676.9723) 
(list 1354.585 676.5223) 
(list 1354.585 676.6993) 
(list 1280.5625 677.0493)))
(apply 'command (append '("pline") coords '("c")))
(setq currobj (ssadd (entlast) currobj))
(setq coords (list 
(list 1280.5625 677.1923) 
(list 1354.585 676.8423) 
(list 1354.585 677.0193) 
(list 1280.5625 677.2693)))
(apply 'command (append '("pline") coords '("c")))
(setq currobj (ssadd (entlast) currobj))
(setq coords (list 
(list 1280.5625 677.4123) 
(list 1354.585 677.1623) 
(list 1354.585 677.3393) 
(list 1280.5625 677.4893)))
(apply 'command (append '("pline") coords '("c")))
(setq currobj (ssadd (entlast) currobj))
(setq coords (list 
(list 1280.5625 677.6323) 
(list 1354.585 677.4823) 
(list 1354.585 677.6593) 
(list 1280.5625 677.7093)))
(apply 'command (append '("pline") coords '("c")))
(setq currobj (ssadd (entlast) currobj))
(setq coords (list 
(list 1280.5625 677.8523) 
(list 1354.585 677.8023) 
(list 1354.585 677.9793) 
(list 1280.5625 677.9293)))
(apply 'command (append '("pline") coords '("c")))
(setq currobj (ssadd (entlast) currobj))
(setq coords (list 
(list 1280.5625 678.0723) 
(list 1354.585 678.1223) 
(list 1354.585 678.2993) 
(list 1280.5625 678.1493)))
(apply 'command (append '("pline") coords '("c")))
(setq currobj (ssadd (entlast) currobj))
(setq coords (list 
(list 1280.5625 678.2923) 
(list 1354.585 678.4423) 
(list 1354.585 678.6193) 
(list 1280.5625 678.3693)))
(apply 'command (append '("pline") coords '("c")))
(setq currobj (ssadd (entlast) currobj))
(setq coords (list 
(list 1280.5625 678.5123) 
(list 1354.585 678.7623) 
(list 1354.585 678.9393) 
(list 1280.5625 678.5893)))
(apply 'command (append '("pline") coords '("c")))
(setq currobj (ssadd (entlast) currobj))
(setq coords (list 
(list 1280.5625 678.7323) 
(list 1354.585 679.0823) 
(list 1354.585 679.2593) 
(list 1280.5625 678.8093)))
(apply 'command (append '("pline") coords '("c")))
(setq currobj (ssadd (entlast) currobj))
(setq coords (list 
(list 1280.5625 678.9523) 
(list 1354.585 679.4023) 
(list 1354.585 679.5793) 
(list 1280.5625 679.0293)))
(apply 'command (append '("pline") coords '("c")))
(setq currobj (ssadd (entlast) currobj))
(setq coords (list 
(list 1280.5625 679.1723) 
(list 1354.585 679.7223) 
(list 1354.585 679.8993) 
(list 1280.5625 679.2493)))
(apply 'command (append '("pline") coords '("c")))
(setq currobj (ssadd (entlast) currobj))
(setq coords (list 
(list 1280.5625 679.3923) 
(list 1354.585 680.0423) 
(list 1354.585 680.2193) 
(list 1280.5625 679.4693)))
(apply 'command (append '("pline") coords '("c")))
(setq currobj (ssadd (entlast) currobj))
(setq coords (list 
(list 1279.4375 679.4693) 
(list 1205.415 680.2193) 
(list 1205.415 680.0423) 
(list 1279.4375 679.3923)))
(apply 'command (append '("pline") coords '("c")))
(setq currobj (ssadd (entlast) currobj))
(setq coords (list 
(list 1279.4375 679.2493) 
(list 1205.415 679.8993) 
(list 1205.415 679.7223) 
(list 1279.4375 679.1723)))
(apply 'command (append '("pline") coords '("c")))
(setq currobj (ssadd (entlast) currobj))
(setq coords (list 
(list 1279.4375 679.0293) 
(list 1205.415 679.5793) 
(list 1205.415 679.4023) 
(list 1279.4375 678.9523)))
(apply 'command (append '("pline") coords '("c")))
(setq currobj (ssadd (entlast) currobj))
(setq coords (list 
(list 1279.4375 678.8093) 
(list 1205.415 679.2593) 
(list 1205.415 679.0823) 
(list 1279.4375 678.7323)))
(apply 'command (append '("pline") coords '("c")))
(setq currobj (ssadd (entlast) currobj))
(setq coords (list 
(list 1279.4375 678.5893) 
(list 1205.415 678.9393) 
(list 1205.415 678.7623) 
(list 1279.4375 678.5123)))
(apply 'command (append '("pline") coords '("c")))
(setq currobj (ssadd (entlast) currobj))
(setq coords (list 
(list 1279.4375 678.3693) 
(list 1205.415 678.6193) 
(list 1205.415 678.4423) 
(list 1279.4375 678.2923)))
(apply 'command (append '("pline") coords '("c")))
(setq currobj (ssadd (entlast) currobj))
(setq coords (list 
(list 1279.4375 678.1493) 
(list 1205.415 678.2993) 
(list 1205.415 678.1223) 
(list 1279.4375 678.0723)))
(apply 'command (append '("pline") coords '("c")))
(setq currobj (ssadd (entlast) currobj))
(setq coords (list 
(list 1279.4375 677.9293) 
(list 1205.415 677.9793) 
(list 1205.415 677.8023) 
(list 1279.4375 677.8523)))
(apply 'command (append '("pline") coords '("c")))
(setq currobj (ssadd (entlast) currobj))
(setq coords (list 
(list 1279.4375 677.7093) 
(list 1205.415 677.6593) 
(list 1205.415 677.4823) 
(list 1279.4375 677.6323)))
(apply 'command (append '("pline") coords '("c")))
(setq currobj (ssadd (entlast) currobj))
(setq coords (list 
(list 1279.4375 677.4893) 
(list 1205.415 677.3393) 
(list 1205.415 677.1623) 
(list 1279.4375 677.4123)))
(apply 'command (append '("pline") coords '("c")))
(setq currobj (ssadd (entlast) currobj))
(setq coords (list 
(list 1279.4375 677.2693) 
(list 1205.415 677.0193) 
(list 1205.415 676.8423) 
(list 1279.4375 677.1923)))
(apply 'command (append '("pline") coords '("c")))
(setq currobj (ssadd (entlast) currobj))
(setq coords (list 
(list 1279.4375 677.0493) 
(list 1205.415 676.6993) 
(list 1205.415 676.5223) 
(list 1279.4375 676.9723)))
(apply 'command (append '("pline") coords '("c")))
(setq currobj (ssadd (entlast) currobj))
(setq coords (list 
(list 1279.4375 676.8293) 
(list 1205.415 676.3793) 
(list 1205.415 676.2023) 
(list 1279.4375 676.7523)))
(apply 'command (append '("pline") coords '("c")))
(setq currobj (ssadd (entlast) currobj))
(setq coords (list 
(list 1279.4375 676.6093) 
(list 1205.415 676.0593) 
(list 1205.415 675.8823) 
(list 1279.4375 676.5323)))
(apply 'command (append '("pline") coords '("c")))
(setq currobj (ssadd (entlast) currobj))
(setq coords (list 
(list 1279.4375 676.3893) 
(list 1205.415 675.7393) 
(list 1205.415 675.5623) 
(list 1279.4375 676.3123)))
(apply 'command (append '("pline") coords '("c")))
(setq currobj (ssadd (entlast) currobj))
(command "_layer" "set" "nitride" "")
(command "_layer" "set" "text" "")
(command "_circle" "1279.0625,665.1693" "0.075")
(command "_circle" "1279.0625,665.4693" "0.075")
(command "_circle" "1279.0625,665.7693" "0.075")
(command "_circle" "1279.0625,666.0693" "0.075")
(command "_circle" "1279.0625,666.3693" "0.075")
(command "_circle" "1278.7625,665.1693" "0.075")
(command "_circle" "1278.7625,665.4693" "0.075")
(command "_circle" "1278.7625,665.7693" "0.075")
(command "_circle" "1278.7625,666.0693" "0.075")
(command "_circle" "1278.7625,666.3693" "0.075")
(command "_circle" "1278.4625,665.1693" "0.075")
(command "_circle" "1278.4625,665.4693" "0.075")
(command "_circle" "1278.4625,665.7693" "0.075")
(command "_circle" "1278.4625,666.0693" "0.075")
(command "_circle" "1278.4625,666.3693" "0.075")
(command "_circle" "1278.1625,665.1693" "0.075")
(command "_circle" "1278.1625,665.4693" "0.075")
(command "_circle" "1278.1625,665.7693" "0.075")
(command "_circle" "1278.1625,666.0693" "0.075")
(command "_circle" "1278.1625,666.3693" "0.075")
(command "_circle" "1277.8625,665.1693" "0.075")
(command "_circle" "1277.8625,665.4693" "0.075")
(command "_circle" "1277.8625,665.7693" "0.075")
(command "_circle" "1277.8625,666.0693" "0.075")
(command "_circle" "1277.8625,666.3693" "0.075")
(command "_layer" "set" "nitride" "")
(setq coords (list 
(list 1280.2625 690.6123) 
(list 1280.2625 806.257) 
(list 1279.7375 806.257) 
(list 1279.7375 690.6123)))
(apply 'command (append '("pline") coords '("c")))
(setq currobj (ssadd (entlast) currobj))
(command "_layer" "set" "prebias" "")
(command "_rectangle" "1279.7375,690.6123" "1280.2625,806.257")
(setq currobj (ssadd (entlast) currobj))
(command "_layer" "set" "nitride" "")
(setq coords (list 
(list 1280.2625 806.257) 
(list 1280.5625 816.257) 
(list 1280.5625 816.257) 
(list 1280.5625 817.257) 
(list 1354.585 816.507) 
(list 1354.585 821.45) 
(list 1280.5625 820.7) 
(list 1280.5625 821.7) 
(list 1280.5625 821.7) 
(list 1280.2625 831.7) 
(list 1279.7375 831.7) 
(list 1279.4375 821.7) 
(list 1279.4375 821.7) 
(list 1279.4375 820.7) 
(list 1205.415 821.45) 
(list 1205.415 816.507) 
(list 1279.4375 817.257) 
(list 1279.4375 816.257) 
(list 1279.4375 816.257) 
(list 1279.7375 806.257)))
(apply 'command (append '("pline") coords '("c")))
(setq currobj (ssadd (entlast) currobj))
(command "_layer" "set" "prebias" "")
(setq coords (list 
(list 1279.4375 806.257) 
(list 1279.4375 817.257) 
(list 1205.415 816.507) 
(list 1205.415 821.45) 
(list 1279.4375 820.7) 
(list 1279.4375 831.7) 
(list 1280.5625 831.7) 
(list 1280.5625 820.7) 
(list 1354.585 821.45) 
(list 1354.585 816.507) 
(list 1280.5625 817.257) 
(list 1280.5625 806.257)))
(apply 'command (append '("pline") coords '("c")))
(setq currobj (ssadd (entlast) currobj))
(command "_layer" "set" "nitride" "")
(command "_layer" "set" "fda1" "")
(setq coords (list 
(list 1280.5625 817.4) 
(list 1354.585 816.65) 
(list 1354.585 816.827) 
(list 1280.5625 817.477)))
(apply 'command (append '("pline") coords '("c")))
(setq currobj (ssadd (entlast) currobj))
(setq coords (list 
(list 1280.5625 817.62) 
(list 1354.585 816.97) 
(list 1354.585 817.147) 
(list 1280.5625 817.697)))
(apply 'command (append '("pline") coords '("c")))
(setq currobj (ssadd (entlast) currobj))
(setq coords (list 
(list 1280.5625 817.84) 
(list 1354.585 817.29) 
(list 1354.585 817.467) 
(list 1280.5625 817.917)))
(apply 'command (append '("pline") coords '("c")))
(setq currobj (ssadd (entlast) currobj))
(setq coords (list 
(list 1280.5625 818.06) 
(list 1354.585 817.61) 
(list 1354.585 817.787) 
(list 1280.5625 818.137)))
(apply 'command (append '("pline") coords '("c")))
(setq currobj (ssadd (entlast) currobj))
(setq coords (list 
(list 1280.5625 818.28) 
(list 1354.585 817.93) 
(list 1354.585 818.107) 
(list 1280.5625 818.357)))
(apply 'command (append '("pline") coords '("c")))
(setq currobj (ssadd (entlast) currobj))
(setq coords (list 
(list 1280.5625 818.5) 
(list 1354.585 818.25) 
(list 1354.585 818.427) 
(list 1280.5625 818.577)))
(apply 'command (append '("pline") coords '("c")))
(setq currobj (ssadd (entlast) currobj))
(setq coords (list 
(list 1280.5625 818.72) 
(list 1354.585 818.57) 
(list 1354.585 818.747) 
(list 1280.5625 818.797)))
(apply 'command (append '("pline") coords '("c")))
(setq currobj (ssadd (entlast) currobj))
(setq coords (list 
(list 1280.5625 818.94) 
(list 1354.585 818.89) 
(list 1354.585 819.067) 
(list 1280.5625 819.017)))
(apply 'command (append '("pline") coords '("c")))
(setq currobj (ssadd (entlast) currobj))
(setq coords (list 
(list 1280.5625 819.16) 
(list 1354.585 819.21) 
(list 1354.585 819.387) 
(list 1280.5625 819.237)))
(apply 'command (append '("pline") coords '("c")))
(setq currobj (ssadd (entlast) currobj))
(setq coords (list 
(list 1280.5625 819.38) 
(list 1354.585 819.53) 
(list 1354.585 819.707) 
(list 1280.5625 819.457)))
(apply 'command (append '("pline") coords '("c")))
(setq currobj (ssadd (entlast) currobj))
(setq coords (list 
(list 1280.5625 819.6) 
(list 1354.585 819.85) 
(list 1354.585 820.027) 
(list 1280.5625 819.677)))
(apply 'command (append '("pline") coords '("c")))
(setq currobj (ssadd (entlast) currobj))
(setq coords (list 
(list 1280.5625 819.82) 
(list 1354.585 820.17) 
(list 1354.585 820.347) 
(list 1280.5625 819.897)))
(apply 'command (append '("pline") coords '("c")))
(setq currobj (ssadd (entlast) currobj))
(setq coords (list 
(list 1280.5625 820.04) 
(list 1354.585 820.49) 
(list 1354.585 820.667) 
(list 1280.5625 820.117)))
(apply 'command (append '("pline") coords '("c")))
(setq currobj (ssadd (entlast) currobj))
(setq coords (list 
(list 1280.5625 820.26) 
(list 1354.585 820.81) 
(list 1354.585 820.987) 
(list 1280.5625 820.337)))
(apply 'command (append '("pline") coords '("c")))
(setq currobj (ssadd (entlast) currobj))
(setq coords (list 
(list 1280.5625 820.48) 
(list 1354.585 821.13) 
(list 1354.585 821.307) 
(list 1280.5625 820.557)))
(apply 'command (append '("pline") coords '("c")))
(setq currobj (ssadd (entlast) currobj))
(setq coords (list 
(list 1279.4375 820.557) 
(list 1205.415 821.307) 
(list 1205.415 821.13) 
(list 1279.4375 820.48)))
(apply 'command (append '("pline") coords '("c")))
(setq currobj (ssadd (entlast) currobj))
(setq coords (list 
(list 1279.4375 820.337) 
(list 1205.415 820.987) 
(list 1205.415 820.81) 
(list 1279.4375 820.26)))
(apply 'command (append '("pline") coords '("c")))
(setq currobj (ssadd (entlast) currobj))
(setq coords (list 
(list 1279.4375 820.117) 
(list 1205.415 820.667) 
(list 1205.415 820.49) 
(list 1279.4375 820.04)))
(apply 'command (append '("pline") coords '("c")))
(setq currobj (ssadd (entlast) currobj))
(setq coords (list 
(list 1279.4375 819.897) 
(list 1205.415 820.347) 
(list 1205.415 820.17) 
(list 1279.4375 819.82)))
(apply 'command (append '("pline") coords '("c")))
(setq currobj (ssadd (entlast) currobj))
(setq coords (list 
(list 1279.4375 819.677) 
(list 1205.415 820.027) 
(list 1205.415 819.85) 
(list 1279.4375 819.6)))
(apply 'command (append '("pline") coords '("c")))
(setq currobj (ssadd (entlast) currobj))
(setq coords (list 
(list 1279.4375 819.457) 
(list 1205.415 819.707) 
(list 1205.415 819.53) 
(list 1279.4375 819.38)))
(apply 'command (append '("pline") coords '("c")))
(setq currobj (ssadd (entlast) currobj))
(setq coords (list 
(list 1279.4375 819.237) 
(list 1205.415 819.387) 
(list 1205.415 819.21) 
(list 1279.4375 819.16)))
(apply 'command (append '("pline") coords '("c")))
(setq currobj (ssadd (entlast) currobj))
(setq coords (list 
(list 1279.4375 819.017) 
(list 1205.415 819.067) 
(list 1205.415 818.89) 
(list 1279.4375 818.94)))
(apply 'command (append '("pline") coords '("c")))
(setq currobj (ssadd (entlast) currobj))
(setq coords (list 
(list 1279.4375 818.797) 
(list 1205.415 818.747) 
(list 1205.415 818.57) 
(list 1279.4375 818.72)))
(apply 'command (append '("pline") coords '("c")))
(setq currobj (ssadd (entlast) currobj))
(setq coords (list 
(list 1279.4375 818.577) 
(list 1205.415 818.427) 
(list 1205.415 818.25) 
(list 1279.4375 818.5)))
(apply 'command (append '("pline") coords '("c")))
(setq currobj (ssadd (entlast) currobj))
(setq coords (list 
(list 1279.4375 818.357) 
(list 1205.415 818.107) 
(list 1205.415 817.93) 
(list 1279.4375 818.28)))
(apply 'command (append '("pline") coords '("c")))
(setq currobj (ssadd (entlast) currobj))
(setq coords (list 
(list 1279.4375 818.137) 
(list 1205.415 817.787) 
(list 1205.415 817.61) 
(list 1279.4375 818.06)))
(apply 'command (append '("pline") coords '("c")))
(setq currobj (ssadd (entlast) currobj))
(setq coords (list 
(list 1279.4375 817.917) 
(list 1205.415 817.467) 
(list 1205.415 817.29) 
(list 1279.4375 817.84)))
(apply 'command (append '("pline") coords '("c")))
(setq currobj (ssadd (entlast) currobj))
(setq coords (list 
(list 1279.4375 817.697) 
(list 1205.415 817.147) 
(list 1205.415 816.97) 
(list 1279.4375 817.62)))
(apply 'command (append '("pline") coords '("c")))
(setq currobj (ssadd (entlast) currobj))
(setq coords (list 
(list 1279.4375 817.477) 
(list 1205.415 816.827) 
(list 1205.415 816.65) 
(list 1279.4375 817.4)))
(apply 'command (append '("pline") coords '("c")))
(setq currobj (ssadd (entlast) currobj))
(command "_layer" "set" "nitride" "")
(command "_layer" "set" "text" "")
(command "_circle" "1279.0625,806.257" "0.075")
(command "_circle" "1279.0625,806.557" "0.075")
(command "_circle" "1279.0625,806.857" "0.075")
(command "_circle" "1279.0625,807.157" "0.075")
(command "_circle" "1279.0625,807.457" "0.075")
(command "_circle" "1278.7625,806.257" "0.075")
(command "_circle" "1278.7625,806.557" "0.075")
(command "_circle" "1278.7625,806.857" "0.075")
(command "_circle" "1278.7625,807.157" "0.075")
(command "_circle" "1278.7625,807.457" "0.075")
(command "_circle" "1278.4625,806.257" "0.075")
(command "_circle" "1278.4625,806.557" "0.075")
(command "_circle" "1278.4625,806.857" "0.075")
(command "_circle" "1278.4625,807.157" "0.075")
(command "_circle" "1278.4625,807.457" "0.075")
(command "_circle" "1278.1625,806.257" "0.075")
(command "_circle" "1278.1625,806.557" "0.075")
(command "_circle" "1278.1625,806.857" "0.075")
(command "_circle" "1278.1625,807.157" "0.075")
(command "_circle" "1278.1625,807.457" "0.075")
(command "_circle" "1277.8625,806.257" "0.075")
(command "_circle" "1277.8625,806.557" "0.075")
(command "_circle" "1277.8625,806.857" "0.075")
(command "_circle" "1277.8625,807.157" "0.075")
(command "_circle" "1277.8625,807.457" "0.075")
(command "_layer" "set" "nitride" "")
(setq coords (list 
(list 1280.2625 831.7) 
(list 1280.2625 836.7) 
(list 1279.7375 836.7) 
(list 1279.7375 831.7)))
(apply 'command (append '("pline") coords '("c")))
(setq currobj (ssadd (entlast) currobj))
(command "_layer" "set" "prebias" "")
(command "_rectangle" "1279.7375,831.7" "1280.2625,836.7")
(setq currobj (ssadd (entlast) currobj))
(command "_layer" "set" "nitride" "")
(setq cooledsinglenanobeam4 currobj)
(setq currobj nil)
(setq currobj (ssadd))
; DRAWING PHOTONIC CRYSTAL
(command "_layer" "set" "negYjunc" "")
(setq coords (list 
(list 1280.135 866.7) 
(list 1280 851.7) 
(list 1280 866.7)))
(apply 'command (append '("pline") coords '("c")))
(setq currobj (ssadd (entlast) currobj))
(setq coords (list 
(list 1280.2625 836.7) 
(list 1280.415 866.7) 
(list 1281.096 866.7) 
(list 1281.096 836.7)))
(apply 'command (append '("pline") coords '("c")))
(setq currobj (ssadd (entlast) currobj))
(setq coords (list 
(list 1279.865 866.7) 
(list 1280 851.7) 
(list 1280 866.7)))
(apply 'command (append '("pline") coords '("c")))
(setq currobj (ssadd (entlast) currobj))
(setq coords (list 
(list 1279.7375 836.7) 
(list 1279.585 866.7) 
(list 1278.904 866.7) 
(list 1278.904 836.7)))
(apply 'command (append '("pline") coords '("c")))
(setq currobj (ssadd (entlast) currobj))
(command "_layer" "set" "nitride" "")
(setq yjunction4 currobj)
(setq currobj nil)
(setq currobj (ssadd))
(setq tap4 nil)
(setq tap4 (ssadd))
(command "_layer" "set" "phc" "")
(setq coords (list 
(list 1280 866.7) 
(list 1280.135 866.7) 
(list 1280.135 866.7103) 
(list 1280.135 866.7206) 
(list 1280.135 866.7308) 
(list 1280.135 866.7411) 
(list 1280.135 866.7514) 
(list 1280.135 866.7617) 
(list 1280.135 866.7719) 
(list 1280.135 866.7822) 
(list 1280.135 866.7925) 
(list 1280.135 866.8028) 
(list 1280.135 866.8131) 
(list 1280.135 866.8233) 
(list 1280.135 866.8336) 
(list 1280.135 866.8439) 
(list 1280.135 866.8542) 
(list 1280.135 866.8644) 
(list 1280.135 866.8747) 
(list 1280.135 866.885) 
(list 1280.135 866.8953) 
(list 1280.135 866.9056) 
(list 1280.135 866.9158) 
(list 1280.135 866.9261) 
(list 1280.135 866.9364) 
(list 1280.135 866.9467) 
(list 1280.135 866.9569) 
(list 1280.135 866.9672) 
(list 1280.135 866.9775) 
(list 1280.135 866.9878) 
(list 1280.135 866.9981) 
(list 1280.135 867.0083) 
(list 1280.135 867.0186) 
(list 1280.135 867.0289) 
(list 1280.135 867.0392) 
(list 1280.135 867.0494) 
(list 1280.135 867.0597) 
(list 1280.135 867.07) 
(list 1280 867.07)))
(apply 'command (append '("pline") coords '("c")))
(setq tap4 (ssadd (entlast) tap4))
(command "_mirror" (entlast) "" "1280,900" "1280,901" "No")
(setq tap4 (ssadd (entlast) tap4))
(setq coords (list 
(list 1280.4239 866.7) 
(list 1280.415 866.7) 
(list 1280.4152 866.7103) 
(list 1280.4155 866.7206) 
(list 1280.4156 866.7308) 
(list 1280.4157 866.7411) 
(list 1280.4158 866.7514) 
(list 1280.4157 866.7617) 
(list 1280.4156 866.7719) 
(list 1280.4153 866.7822) 
(list 1280.4149 866.7925) 
(list 1280.4145 866.8028) 
(list 1280.414 866.8131) 
(list 1280.4134 866.8233) 
(list 1280.4128 866.8336) 
(list 1280.4122 866.8439) 
(list 1280.4116 866.8542) 
(list 1280.4111 866.8644) 
(list 1280.4106 866.8747) 
(list 1280.4103 866.885) 
(list 1280.4101 866.8953) 
(list 1280.4101 866.9056) 
(list 1280.4102 866.9158) 
(list 1280.4106 866.9261) 
(list 1280.4111 866.9364) 
(list 1280.4118 866.9467) 
(list 1280.4126 866.9569) 
(list 1280.4137 866.9672) 
(list 1280.4148 866.9775) 
(list 1280.416 866.9878) 
(list 1280.4173 866.9981) 
(list 1280.4186 867.0083) 
(list 1280.4198 867.0186) 
(list 1280.421 867.0289) 
(list 1280.422 867.0392) 
(list 1280.4229 867.0494) 
(list 1280.4235 867.0597) 
(list 1280.4239 867.07) 
(list 1280.4239 867.07)))
(apply 'command (append '("pline") coords '("c")))
(setq tap4 (ssadd (entlast) tap4))
(command "_mirror" (entlast) "" "1280,900" "1280,901" "No")
(setq tap4 (ssadd (entlast) tap4))
(setq coords (list 
(list 1281.096 866.7) 
(list 1280.4239 866.7) 
(list 1280.4239 866.7103) 
(list 1280.4239 866.7206) 
(list 1280.4239 866.7308) 
(list 1280.4239 866.7411) 
(list 1280.4239 866.7514) 
(list 1280.4239 866.7617) 
(list 1280.4239 866.7719) 
(list 1280.4239 866.7822) 
(list 1280.4239 866.7925) 
(list 1280.4239 866.8028) 
(list 1280.4239 866.8131) 
(list 1280.4239 866.8233) 
(list 1280.4239 866.8336) 
(list 1280.4239 866.8439) 
(list 1280.4239 866.8542) 
(list 1280.4239 866.8644) 
(list 1280.4239 866.8747) 
(list 1280.4239 866.885) 
(list 1280.4239 866.8953) 
(list 1280.4239 866.9056) 
(list 1280.4239 866.9158) 
(list 1280.4239 866.9261) 
(list 1280.4239 866.9364) 
(list 1280.4239 866.9467) 
(list 1280.4239 866.9569) 
(list 1280.4239 866.9672) 
(list 1280.4239 866.9775) 
(list 1280.4239 866.9878) 
(list 1280.4239 866.9981) 
(list 1280.4239 867.0083) 
(list 1280.4239 867.0186) 
(list 1280.4239 867.0289) 
(list 1280.4239 867.0392) 
(list 1280.4239 867.0494) 
(list 1280.4239 867.0597) 
(list 1280.4239 867.07) 
(list 1281.096 867.07)))
(apply 'command (append '("pline") coords '("c")))
(setq tap4 (ssadd (entlast) tap4))
(command "_mirror" (entlast) "" "1280,900" "1280,901" "No")
(setq tap4 (ssadd (entlast) tap4))
(setq coords (list 
(list 1280 867.07) 
(list 1280.135 867.07) 
(list 1280.135 867.0803) 
(list 1280.135 867.0906) 
(list 1280.135 867.1008) 
(list 1280.135 867.1111) 
(list 1280.135 867.1214) 
(list 1280.135 867.1317) 
(list 1280.135 867.1419) 
(list 1280.135 867.1522) 
(list 1280.135 867.1625) 
(list 1280.135 867.1728) 
(list 1280.135 867.1831) 
(list 1280.135 867.1933) 
(list 1280.135 867.2036) 
(list 1280.135 867.2139) 
(list 1280.135 867.2242) 
(list 1280.135 867.2344) 
(list 1280.135 867.2447) 
(list 1280.135 867.255) 
(list 1280.135 867.2653) 
(list 1280.135 867.2756) 
(list 1280.135 867.2858) 
(list 1280.135 867.2961) 
(list 1280.135 867.3064) 
(list 1280.135 867.3167) 
(list 1280.135 867.3269) 
(list 1280.135 867.3372) 
(list 1280.135 867.3475) 
(list 1280.135 867.3578) 
(list 1280.135 867.3681) 
(list 1280.135 867.3783) 
(list 1280.135 867.3886) 
(list 1280.135 867.3989) 
(list 1280.135 867.4092) 
(list 1280.135 867.4194) 
(list 1280.135 867.4297) 
(list 1280.135 867.44) 
(list 1280 867.44)))
(apply 'command (append '("pline") coords '("c")))
(setq tap4 (ssadd (entlast) tap4))
(command "_mirror" (entlast) "" "1280,900" "1280,901" "No")
(setq tap4 (ssadd (entlast) tap4))
(setq coords (list 
(list 1280.4327 867.07) 
(list 1280.4239 867.07) 
(list 1280.424 867.0803) 
(list 1280.4238 867.0906) 
(list 1280.4233 867.1008) 
(list 1280.4225 867.1111) 
(list 1280.4214 867.1214) 
(list 1280.42 867.1317) 
(list 1280.4184 867.1419) 
(list 1280.4166 867.1522) 
(list 1280.4147 867.1625) 
(list 1280.4126 867.1728) 
(list 1280.4106 867.1831) 
(list 1280.4086 867.1933) 
(list 1280.4066 867.2036) 
(list 1280.4049 867.2139) 
(list 1280.4034 867.2242) 
(list 1280.4022 867.2344) 
(list 1280.4014 867.2447) 
(list 1280.4009 867.255) 
(list 1280.4009 867.2653) 
(list 1280.4012 867.2756) 
(list 1280.4021 867.2858) 
(list 1280.4033 867.2961) 
(list 1280.4049 867.3064) 
(list 1280.4069 867.3167) 
(list 1280.4093 867.3269) 
(list 1280.4118 867.3372) 
(list 1280.4145 867.3475) 
(list 1280.4173 867.3578) 
(list 1280.4202 867.3681) 
(list 1280.4229 867.3783) 
(list 1280.4254 867.3886) 
(list 1280.4277 867.3989) 
(list 1280.4296 867.4092) 
(list 1280.4312 867.4194) 
(list 1280.4322 867.4297) 
(list 1280.4327 867.44) 
(list 1280.4327 867.44)))
(apply 'command (append '("pline") coords '("c")))
(setq tap4 (ssadd (entlast) tap4))
(command "_mirror" (entlast) "" "1280,900" "1280,901" "No")
(setq tap4 (ssadd (entlast) tap4))
(setq coords (list 
(list 1281.096 867.07) 
(list 1280.4327 867.07) 
(list 1280.4327 867.0803) 
(list 1280.4327 867.0906) 
(list 1280.4327 867.1008) 
(list 1280.4327 867.1111) 
(list 1280.4327 867.1214) 
(list 1280.4327 867.1317) 
(list 1280.4327 867.1419) 
(list 1280.4327 867.1522) 
(list 1280.4327 867.1625) 
(list 1280.4327 867.1728) 
(list 1280.4327 867.1831) 
(list 1280.4327 867.1933) 
(list 1280.4327 867.2036) 
(list 1280.4327 867.2139) 
(list 1280.4327 867.2242) 
(list 1280.4327 867.2344) 
(list 1280.4327 867.2447) 
(list 1280.4327 867.255) 
(list 1280.4327 867.2653) 
(list 1280.4327 867.2756) 
(list 1280.4327 867.2858) 
(list 1280.4327 867.2961) 
(list 1280.4327 867.3064) 
(list 1280.4327 867.3167) 
(list 1280.4327 867.3269) 
(list 1280.4327 867.3372) 
(list 1280.4327 867.3475) 
(list 1280.4327 867.3578) 
(list 1280.4327 867.3681) 
(list 1280.4327 867.3783) 
(list 1280.4327 867.3886) 
(list 1280.4327 867.3989) 
(list 1280.4327 867.4092) 
(list 1280.4327 867.4194) 
(list 1280.4327 867.4297) 
(list 1280.4327 867.44) 
(list 1281.096 867.44)))
(apply 'command (append '("pline") coords '("c")))
(setq tap4 (ssadd (entlast) tap4))
(command "_mirror" (entlast) "" "1280,900" "1280,901" "No")
(setq tap4 (ssadd (entlast) tap4))
(setq coords (list 
(list 1280 867.44) 
(list 1280.135 867.44) 
(list 1280.135 867.4503) 
(list 1280.135 867.4606) 
(list 1280.135 867.4708) 
(list 1280.135 867.4811) 
(list 1280.135 867.4914) 
(list 1280.135 867.5017) 
(list 1280.135 867.5119) 
(list 1280.135 867.5222) 
(list 1280.135 867.5325) 
(list 1280.135 867.5428) 
(list 1280.135 867.5531) 
(list 1280.135 867.5633) 
(list 1280.135 867.5736) 
(list 1280.135 867.5839) 
(list 1280.135 867.5942) 
(list 1280.135 867.6044) 
(list 1280.135 867.6147) 
(list 1280.135 867.625) 
(list 1280.135 867.6353) 
(list 1280.135 867.6456) 
(list 1280.135 867.6558) 
(list 1280.135 867.6661) 
(list 1280.135 867.6764) 
(list 1280.135 867.6867) 
(list 1280.135 867.6969) 
(list 1280.135 867.7072) 
(list 1280.135 867.7175) 
(list 1280.135 867.7278) 
(list 1280.135 867.7381) 
(list 1280.135 867.7483) 
(list 1280.135 867.7586) 
(list 1280.135 867.7689) 
(list 1280.135 867.7792) 
(list 1280.135 867.7894) 
(list 1280.135 867.7997) 
(list 1280.135 867.81) 
(list 1280 867.81)))
(apply 'command (append '("pline") coords '("c")))
(setq tap4 (ssadd (entlast) tap4))
(command "_mirror" (entlast) "" "1280,900" "1280,901" "No")
(setq tap4 (ssadd (entlast) tap4))
(setq coords (list 
(list 1280.4416 867.44) 
(list 1280.4327 867.44) 
(list 1280.4327 867.4503) 
(list 1280.4321 867.4606) 
(list 1280.4309 867.4708) 
(list 1280.4292 867.4811) 
(list 1280.427 867.4914) 
(list 1280.4243 867.5017) 
(list 1280.4213 867.5119) 
(list 1280.4179 867.5222) 
(list 1280.4144 867.5325) 
(list 1280.4108 867.5428) 
(list 1280.4072 867.5531) 
(list 1280.4037 867.5633) 
(list 1280.4005 867.5736) 
(list 1280.3976 867.5839) 
(list 1280.3952 867.5942) 
(list 1280.3934 867.6044) 
(list 1280.3921 867.6147) 
(list 1280.3915 867.625) 
(list 1280.3916 867.6353) 
(list 1280.3924 867.6456) 
(list 1280.3939 867.6558) 
(list 1280.396 867.6661) 
(list 1280.3988 867.6764) 
(list 1280.4021 867.6867) 
(list 1280.4059 867.6969) 
(list 1280.41 867.7072) 
(list 1280.4143 867.7175) 
(list 1280.4187 867.7278) 
(list 1280.423 867.7381) 
(list 1280.4272 867.7483) 
(list 1280.431 867.7586) 
(list 1280.4344 867.7689) 
(list 1280.4373 867.7792) 
(list 1280.4395 867.7894) 
(list 1280.4409 867.7997) 
(list 1280.4416 867.81) 
(list 1280.4416 867.81)))
(apply 'command (append '("pline") coords '("c")))
(setq tap4 (ssadd (entlast) tap4))
(command "_mirror" (entlast) "" "1280,900" "1280,901" "No")
(setq tap4 (ssadd (entlast) tap4))
(setq coords (list 
(list 1281.096 867.44) 
(list 1280.4416 867.44) 
(list 1280.4416 867.4503) 
(list 1280.4416 867.4606) 
(list 1280.4416 867.4708) 
(list 1280.4416 867.4811) 
(list 1280.4416 867.4914) 
(list 1280.4416 867.5017) 
(list 1280.4416 867.5119) 
(list 1280.4416 867.5222) 
(list 1280.4416 867.5325) 
(list 1280.4416 867.5428) 
(list 1280.4416 867.5531) 
(list 1280.4416 867.5633) 
(list 1280.4416 867.5736) 
(list 1280.4416 867.5839) 
(list 1280.4416 867.5942) 
(list 1280.4416 867.6044) 
(list 1280.4416 867.6147) 
(list 1280.4416 867.625) 
(list 1280.4416 867.6353) 
(list 1280.4416 867.6456) 
(list 1280.4416 867.6558) 
(list 1280.4416 867.6661) 
(list 1280.4416 867.6764) 
(list 1280.4416 867.6867) 
(list 1280.4416 867.6969) 
(list 1280.4416 867.7072) 
(list 1280.4416 867.7175) 
(list 1280.4416 867.7278) 
(list 1280.4416 867.7381) 
(list 1280.4416 867.7483) 
(list 1280.4416 867.7586) 
(list 1280.4416 867.7689) 
(list 1280.4416 867.7792) 
(list 1280.4416 867.7894) 
(list 1280.4416 867.7997) 
(list 1280.4416 867.81) 
(list 1281.096 867.81)))
(apply 'command (append '("pline") coords '("c")))
(setq tap4 (ssadd (entlast) tap4))
(command "_mirror" (entlast) "" "1280,900" "1280,901" "No")
(setq tap4 (ssadd (entlast) tap4))
(setq coords (list 
(list 1280 867.81) 
(list 1280.135 867.81) 
(list 1280.135 867.8203) 
(list 1280.135 867.8306) 
(list 1280.135 867.8408) 
(list 1280.135 867.8511) 
(list 1280.135 867.8614) 
(list 1280.135 867.8717) 
(list 1280.135 867.8819) 
(list 1280.135 867.8922) 
(list 1280.135 867.9025) 
(list 1280.135 867.9128) 
(list 1280.135 867.9231) 
(list 1280.135 867.9333) 
(list 1280.135 867.9436) 
(list 1280.135 867.9539) 
(list 1280.135 867.9642) 
(list 1280.135 867.9744) 
(list 1280.135 867.9847) 
(list 1280.135 867.995) 
(list 1280.135 868.0053) 
(list 1280.135 868.0156) 
(list 1280.135 868.0258) 
(list 1280.135 868.0361) 
(list 1280.135 868.0464) 
(list 1280.135 868.0567) 
(list 1280.135 868.0669) 
(list 1280.135 868.0772) 
(list 1280.135 868.0875) 
(list 1280.135 868.0978) 
(list 1280.135 868.1081) 
(list 1280.135 868.1183) 
(list 1280.135 868.1286) 
(list 1280.135 868.1389) 
(list 1280.135 868.1492) 
(list 1280.135 868.1594) 
(list 1280.135 868.1697) 
(list 1280.135 868.18) 
(list 1280 868.18)))
(apply 'command (append '("pline") coords '("c")))
(setq tap4 (ssadd (entlast) tap4))
(command "_mirror" (entlast) "" "1280,900" "1280,901" "No")
(setq tap4 (ssadd (entlast) tap4))
(setq coords (list 
(list 1280.4505 867.81) 
(list 1280.4416 867.81) 
(list 1280.4414 867.8203) 
(list 1280.4404 867.8306) 
(list 1280.4386 867.8408) 
(list 1280.4359 867.8511) 
(list 1280.4326 867.8614) 
(list 1280.4286 867.8717) 
(list 1280.4241 867.8819) 
(list 1280.4193 867.8922) 
(list 1280.4141 867.9025) 
(list 1280.4089 867.9128) 
(list 1280.4038 867.9231) 
(list 1280.3989 867.9333) 
(list 1280.3944 867.9436) 
(list 1280.3904 867.9539) 
(list 1280.3871 867.9642) 
(list 1280.3845 867.9744) 
(list 1280.3828 867.9847) 
(list 1280.3821 867.995) 
(list 1280.3823 868.0053) 
(list 1280.3835 868.0156) 
(list 1280.3857 868.0258) 
(list 1280.3888 868.0361) 
(list 1280.3927 868.0464) 
(list 1280.3973 868.0567) 
(list 1280.4025 868.0669) 
(list 1280.4081 868.0772) 
(list 1280.414 868.0875) 
(list 1280.42 868.0978) 
(list 1280.4259 868.1081) 
(list 1280.4315 868.1183) 
(list 1280.4366 868.1286) 
(list 1280.4412 868.1389) 
(list 1280.4449 868.1492) 
(list 1280.4478 868.1594) 
(list 1280.4497 868.1697) 
(list 1280.4505 868.18) 
(list 1280.4505 868.18)))
(apply 'command (append '("pline") coords '("c")))
(setq tap4 (ssadd (entlast) tap4))
(command "_mirror" (entlast) "" "1280,900" "1280,901" "No")
(setq tap4 (ssadd (entlast) tap4))
(setq coords (list 
(list 1281.096 867.81) 
(list 1280.4505 867.81) 
(list 1280.4505 867.8203) 
(list 1280.4505 867.8306) 
(list 1280.4505 867.8408) 
(list 1280.4505 867.8511) 
(list 1280.4505 867.8614) 
(list 1280.4505 867.8717) 
(list 1280.4505 867.8819) 
(list 1280.4505 867.8922) 
(list 1280.4505 867.9025) 
(list 1280.4505 867.9128) 
(list 1280.4505 867.9231) 
(list 1280.4505 867.9333) 
(list 1280.4505 867.9436) 
(list 1280.4505 867.9539) 
(list 1280.4505 867.9642) 
(list 1280.4505 867.9744) 
(list 1280.4505 867.9847) 
(list 1280.4505 867.995) 
(list 1280.4505 868.0053) 
(list 1280.4505 868.0156) 
(list 1280.4505 868.0258) 
(list 1280.4505 868.0361) 
(list 1280.4505 868.0464) 
(list 1280.4505 868.0567) 
(list 1280.4505 868.0669) 
(list 1280.4505 868.0772) 
(list 1280.4505 868.0875) 
(list 1280.4505 868.0978) 
(list 1280.4505 868.1081) 
(list 1280.4505 868.1183) 
(list 1280.4505 868.1286) 
(list 1280.4505 868.1389) 
(list 1280.4505 868.1492) 
(list 1280.4505 868.1594) 
(list 1280.4505 868.1697) 
(list 1280.4505 868.18) 
(list 1281.096 868.18)))
(apply 'command (append '("pline") coords '("c")))
(setq tap4 (ssadd (entlast) tap4))
(command "_mirror" (entlast) "" "1280,900" "1280,901" "No")
(setq tap4 (ssadd (entlast) tap4))
(setq coords (list 
(list 1280 868.18) 
(list 1280.135 868.18) 
(list 1280.135 868.1903) 
(list 1280.135 868.2006) 
(list 1280.135 868.2108) 
(list 1280.135 868.2211) 
(list 1280.135 868.2314) 
(list 1280.135 868.2417) 
(list 1280.135 868.2519) 
(list 1280.135 868.2622) 
(list 1280.135 868.2725) 
(list 1280.135 868.2828) 
(list 1280.135 868.2931) 
(list 1280.135 868.3033) 
(list 1280.135 868.3136) 
(list 1280.135 868.3239) 
(list 1280.135 868.3342) 
(list 1280.135 868.3444) 
(list 1280.135 868.3547) 
(list 1280.135 868.365) 
(list 1280.135 868.3753) 
(list 1280.135 868.3856) 
(list 1280.135 868.3958) 
(list 1280.135 868.4061) 
(list 1280.135 868.4164) 
(list 1280.135 868.4267) 
(list 1280.135 868.4369) 
(list 1280.135 868.4472) 
(list 1280.135 868.4575) 
(list 1280.135 868.4678) 
(list 1280.135 868.4781) 
(list 1280.135 868.4883) 
(list 1280.135 868.4986) 
(list 1280.135 868.5089) 
(list 1280.135 868.5192) 
(list 1280.135 868.5294) 
(list 1280.135 868.5397) 
(list 1280.135 868.55) 
(list 1280 868.55)))
(apply 'command (append '("pline") coords '("c")))
(setq tap4 (ssadd (entlast) tap4))
(command "_mirror" (entlast) "" "1280,900" "1280,901" "No")
(setq tap4 (ssadd (entlast) tap4))
(setq coords (list 
(list 1280.4593 868.18) 
(list 1280.4505 868.18) 
(list 1280.4502 868.1903) 
(list 1280.4487 868.2006) 
(list 1280.4462 868.2108) 
(list 1280.4427 868.2211) 
(list 1280.4382 868.2314) 
(list 1280.4329 868.2417) 
(list 1280.427 868.2519) 
(list 1280.4206 868.2622) 
(list 1280.4139 868.2725) 
(list 1280.4071 868.2828) 
(list 1280.4004 868.2931) 
(list 1280.3941 868.3033) 
(list 1280.3882 868.3136) 
(list 1280.3831 868.3239) 
(list 1280.3789 868.3342) 
(list 1280.3757 868.3444) 
(list 1280.3736 868.3547) 
(list 1280.3727 868.365) 
(list 1280.3731 868.3753) 
(list 1280.3747 868.3856) 
(list 1280.3775 868.3958) 
(list 1280.3815 868.4061) 
(list 1280.3865 868.4164) 
(list 1280.3924 868.4267) 
(list 1280.3991 868.4369) 
(list 1280.4063 868.4472) 
(list 1280.4137 868.4575) 
(list 1280.4213 868.4678) 
(list 1280.4287 868.4781) 
(list 1280.4358 868.4883) 
(list 1280.4422 868.4986) 
(list 1280.4479 868.5089) 
(list 1280.4526 868.5192) 
(list 1280.4561 868.5294) 
(list 1280.4584 868.5397) 
(list 1280.4593 868.55) 
(list 1280.4593 868.55)))
(apply 'command (append '("pline") coords '("c")))
(setq tap4 (ssadd (entlast) tap4))
(command "_mirror" (entlast) "" "1280,900" "1280,901" "No")
(setq tap4 (ssadd (entlast) tap4))
(setq coords (list 
(list 1281.096 868.18) 
(list 1280.4593 868.18) 
(list 1280.4593 868.1903) 
(list 1280.4593 868.2006) 
(list 1280.4593 868.2108) 
(list 1280.4593 868.2211) 
(list 1280.4593 868.2314) 
(list 1280.4593 868.2417) 
(list 1280.4593 868.2519) 
(list 1280.4593 868.2622) 
(list 1280.4593 868.2725) 
(list 1280.4593 868.2828) 
(list 1280.4593 868.2931) 
(list 1280.4593 868.3033) 
(list 1280.4593 868.3136) 
(list 1280.4593 868.3239) 
(list 1280.4593 868.3342) 
(list 1280.4593 868.3444) 
(list 1280.4593 868.3547) 
(list 1280.4593 868.365) 
(list 1280.4593 868.3753) 
(list 1280.4593 868.3856) 
(list 1280.4593 868.3958) 
(list 1280.4593 868.4061) 
(list 1280.4593 868.4164) 
(list 1280.4593 868.4267) 
(list 1280.4593 868.4369) 
(list 1280.4593 868.4472) 
(list 1280.4593 868.4575) 
(list 1280.4593 868.4678) 
(list 1280.4593 868.4781) 
(list 1280.4593 868.4883) 
(list 1280.4593 868.4986) 
(list 1280.4593 868.5089) 
(list 1280.4593 868.5192) 
(list 1280.4593 868.5294) 
(list 1280.4593 868.5397) 
(list 1280.4593 868.55) 
(list 1281.096 868.55)))
(apply 'command (append '("pline") coords '("c")))
(setq tap4 (ssadd (entlast) tap4))
(command "_mirror" (entlast) "" "1280,900" "1280,901" "No")
(setq tap4 (ssadd (entlast) tap4))
(setq coords (list 
(list 1280 868.55) 
(list 1280.135 868.55) 
(list 1280.135 868.5603) 
(list 1280.135 868.5706) 
(list 1280.135 868.5808) 
(list 1280.135 868.5911) 
(list 1280.135 868.6014) 
(list 1280.135 868.6117) 
(list 1280.135 868.6219) 
(list 1280.135 868.6322) 
(list 1280.135 868.6425) 
(list 1280.135 868.6528) 
(list 1280.135 868.6631) 
(list 1280.135 868.6733) 
(list 1280.135 868.6836) 
(list 1280.135 868.6939) 
(list 1280.135 868.7042) 
(list 1280.135 868.7144) 
(list 1280.135 868.7247) 
(list 1280.135 868.735) 
(list 1280.135 868.7453) 
(list 1280.135 868.7556) 
(list 1280.135 868.7658) 
(list 1280.135 868.7761) 
(list 1280.135 868.7864) 
(list 1280.135 868.7967) 
(list 1280.135 868.8069) 
(list 1280.135 868.8172) 
(list 1280.135 868.8275) 
(list 1280.135 868.8378) 
(list 1280.135 868.8481) 
(list 1280.135 868.8583) 
(list 1280.135 868.8686) 
(list 1280.135 868.8789) 
(list 1280.135 868.8892) 
(list 1280.135 868.8994) 
(list 1280.135 868.9097) 
(list 1280.135 868.92) 
(list 1280 868.92)))
(apply 'command (append '("pline") coords '("c")))
(setq tap4 (ssadd (entlast) tap4))
(command "_mirror" (entlast) "" "1280,900" "1280,901" "No")
(setq tap4 (ssadd (entlast) tap4))
(setq coords (list 
(list 1280.4682 868.55) 
(list 1280.4593 868.55) 
(list 1280.4589 868.5603) 
(list 1280.457 868.5706) 
(list 1280.4539 868.5808) 
(list 1280.4494 868.5911) 
(list 1280.4438 868.6014) 
(list 1280.4372 868.6117) 
(list 1280.4298 868.6219) 
(list 1280.4219 868.6322) 
(list 1280.4136 868.6425) 
(list 1280.4052 868.6528) 
(list 1280.397 868.6631) 
(list 1280.3892 868.6733) 
(list 1280.3821 868.6836) 
(list 1280.3759 868.6939) 
(list 1280.3707 868.7042) 
(list 1280.3668 868.7144) 
(list 1280.3643 868.7247) 
(list 1280.3633 868.735) 
(list 1280.3638 868.7453) 
(list 1280.3658 868.7556) 
(list 1280.3693 868.7658) 
(list 1280.3742 868.7761) 
(list 1280.3804 868.7864) 
(list 1280.3876 868.7967) 
(list 1280.3957 868.8069) 
(list 1280.4044 868.8172) 
(list 1280.4135 868.8275) 
(list 1280.4226 868.8378) 
(list 1280.4316 868.8481) 
(list 1280.4401 868.8583) 
(list 1280.4478 868.8686) 
(list 1280.4546 868.8789) 
(list 1280.4602 868.8892) 
(list 1280.4644 868.8994) 
(list 1280.4671 868.9097) 
(list 1280.4682 868.92) 
(list 1280.4682 868.92)))
(apply 'command (append '("pline") coords '("c")))
(setq tap4 (ssadd (entlast) tap4))
(command "_mirror" (entlast) "" "1280,900" "1280,901" "No")
(setq tap4 (ssadd (entlast) tap4))
(setq coords (list 
(list 1281.096 868.55) 
(list 1280.4682 868.55) 
(list 1280.4682 868.5603) 
(list 1280.4682 868.5706) 
(list 1280.4682 868.5808) 
(list 1280.4682 868.5911) 
(list 1280.4682 868.6014) 
(list 1280.4682 868.6117) 
(list 1280.4682 868.6219) 
(list 1280.4682 868.6322) 
(list 1280.4682 868.6425) 
(list 1280.4682 868.6528) 
(list 1280.4682 868.6631) 
(list 1280.4682 868.6733) 
(list 1280.4682 868.6836) 
(list 1280.4682 868.6939) 
(list 1280.4682 868.7042) 
(list 1280.4682 868.7144) 
(list 1280.4682 868.7247) 
(list 1280.4682 868.735) 
(list 1280.4682 868.7453) 
(list 1280.4682 868.7556) 
(list 1280.4682 868.7658) 
(list 1280.4682 868.7761) 
(list 1280.4682 868.7864) 
(list 1280.4682 868.7967) 
(list 1280.4682 868.8069) 
(list 1280.4682 868.8172) 
(list 1280.4682 868.8275) 
(list 1280.4682 868.8378) 
(list 1280.4682 868.8481) 
(list 1280.4682 868.8583) 
(list 1280.4682 868.8686) 
(list 1280.4682 868.8789) 
(list 1280.4682 868.8892) 
(list 1280.4682 868.8994) 
(list 1280.4682 868.9097) 
(list 1280.4682 868.92) 
(list 1281.096 868.92)))
(apply 'command (append '("pline") coords '("c")))
(setq tap4 (ssadd (entlast) tap4))
(command "_mirror" (entlast) "" "1280,900" "1280,901" "No")
(setq tap4 (ssadd (entlast) tap4))
(setq coords (list 
(list 1280 868.92) 
(list 1280.135 868.92) 
(list 1280.135 868.9303) 
(list 1280.135 868.9406) 
(list 1280.135 868.9508) 
(list 1280.135 868.9611) 
(list 1280.135 868.9714) 
(list 1280.135 868.9817) 
(list 1280.135 868.9919) 
(list 1280.135 869.0022) 
(list 1280.135 869.0125) 
(list 1280.135 869.0228) 
(list 1280.135 869.0331) 
(list 1280.135 869.0433) 
(list 1280.135 869.0536) 
(list 1280.135 869.0639) 
(list 1280.135 869.0742) 
(list 1280.135 869.0844) 
(list 1280.135 869.0947) 
(list 1280.135 869.105) 
(list 1280.135 869.1153) 
(list 1280.135 869.1256) 
(list 1280.135 869.1358) 
(list 1280.135 869.1461) 
(list 1280.135 869.1564) 
(list 1280.135 869.1667) 
(list 1280.135 869.1769) 
(list 1280.135 869.1872) 
(list 1280.135 869.1975) 
(list 1280.135 869.2078) 
(list 1280.135 869.2181) 
(list 1280.135 869.2283) 
(list 1280.135 869.2386) 
(list 1280.135 869.2489) 
(list 1280.135 869.2592) 
(list 1280.135 869.2694) 
(list 1280.135 869.2797) 
(list 1280.135 869.29) 
(list 1280 869.29)))
(apply 'command (append '("pline") coords '("c")))
(setq tap4 (ssadd (entlast) tap4))
(command "_mirror" (entlast) "" "1280,900" "1280,901" "No")
(setq tap4 (ssadd (entlast) tap4))
(setq coords (list 
(list 1280.4771 868.92) 
(list 1280.4682 868.92) 
(list 1280.4676 868.9303) 
(list 1280.4654 868.9406) 
(list 1280.4615 868.9508) 
(list 1280.4561 868.9611) 
(list 1280.4494 868.9714) 
(list 1280.4415 868.9817) 
(list 1280.4327 868.9919) 
(list 1280.4232 869.0022) 
(list 1280.4133 869.0125) 
(list 1280.4034 869.0228) 
(list 1280.3936 869.0331) 
(list 1280.3844 869.0433) 
(list 1280.376 869.0536) 
(list 1280.3686 869.0639) 
(list 1280.3625 869.0742) 
(list 1280.358 869.0844) 
(list 1280.3551 869.0947) 
(list 1280.3539 869.105) 
(list 1280.3545 869.1153) 
(list 1280.357 869.1256) 
(list 1280.3612 869.1358) 
(list 1280.367 869.1461) 
(list 1280.3743 869.1564) 
(list 1280.3828 869.1667) 
(list 1280.3923 869.1769) 
(list 1280.4025 869.1872) 
(list 1280.4132 869.1975) 
(list 1280.4239 869.2078) 
(list 1280.4344 869.2181) 
(list 1280.4444 869.2283) 
(list 1280.4534 869.2386) 
(list 1280.4614 869.2489) 
(list 1280.4679 869.2592) 
(list 1280.4727 869.2694) 
(list 1280.4759 869.2797) 
(list 1280.4771 869.29) 
(list 1280.4771 869.29)))
(apply 'command (append '("pline") coords '("c")))
(setq tap4 (ssadd (entlast) tap4))
(command "_mirror" (entlast) "" "1280,900" "1280,901" "No")
(setq tap4 (ssadd (entlast) tap4))
(setq coords (list 
(list 1281.096 868.92) 
(list 1280.4771 868.92) 
(list 1280.4771 868.9303) 
(list 1280.4771 868.9406) 
(list 1280.4771 868.9508) 
(list 1280.4771 868.9611) 
(list 1280.4771 868.9714) 
(list 1280.4771 868.9817) 
(list 1280.4771 868.9919) 
(list 1280.4771 869.0022) 
(list 1280.4771 869.0125) 
(list 1280.4771 869.0228) 
(list 1280.4771 869.0331) 
(list 1280.4771 869.0433) 
(list 1280.4771 869.0536) 
(list 1280.4771 869.0639) 
(list 1280.4771 869.0742) 
(list 1280.4771 869.0844) 
(list 1280.4771 869.0947) 
(list 1280.4771 869.105) 
(list 1280.4771 869.1153) 
(list 1280.4771 869.1256) 
(list 1280.4771 869.1358) 
(list 1280.4771 869.1461) 
(list 1280.4771 869.1564) 
(list 1280.4771 869.1667) 
(list 1280.4771 869.1769) 
(list 1280.4771 869.1872) 
(list 1280.4771 869.1975) 
(list 1280.4771 869.2078) 
(list 1280.4771 869.2181) 
(list 1280.4771 869.2283) 
(list 1280.4771 869.2386) 
(list 1280.4771 869.2489) 
(list 1280.4771 869.2592) 
(list 1280.4771 869.2694) 
(list 1280.4771 869.2797) 
(list 1280.4771 869.29) 
(list 1281.096 869.29)))
(apply 'command (append '("pline") coords '("c")))
(setq tap4 (ssadd (entlast) tap4))
(command "_mirror" (entlast) "" "1280,900" "1280,901" "No")
(setq tap4 (ssadd (entlast) tap4))
(setq coords (list 
(list 1280 869.29) 
(list 1280.135 869.29) 
(list 1280.135 869.3003) 
(list 1280.135 869.3106) 
(list 1280.135 869.3208) 
(list 1280.135 869.3311) 
(list 1280.135 869.3414) 
(list 1280.135 869.3517) 
(list 1280.135 869.3619) 
(list 1280.135 869.3722) 
(list 1280.135 869.3825) 
(list 1280.135 869.3928) 
(list 1280.135 869.4031) 
(list 1280.135 869.4133) 
(list 1280.135 869.4236) 
(list 1280.135 869.4339) 
(list 1280.135 869.4442) 
(list 1280.135 869.4544) 
(list 1280.135 869.4647) 
(list 1280.135 869.475) 
(list 1280.135 869.4853) 
(list 1280.135 869.4956) 
(list 1280.135 869.5058) 
(list 1280.135 869.5161) 
(list 1280.135 869.5264) 
(list 1280.135 869.5367) 
(list 1280.135 869.5469) 
(list 1280.135 869.5572) 
(list 1280.135 869.5675) 
(list 1280.135 869.5778) 
(list 1280.135 869.5881) 
(list 1280.135 869.5983) 
(list 1280.135 869.6086) 
(list 1280.135 869.6189) 
(list 1280.135 869.6292) 
(list 1280.135 869.6394) 
(list 1280.135 869.6497) 
(list 1280.135 869.66) 
(list 1280 869.66)))
(apply 'command (append '("pline") coords '("c")))
(setq tap4 (ssadd (entlast) tap4))
(command "_mirror" (entlast) "" "1280,900" "1280,901" "No")
(setq tap4 (ssadd (entlast) tap4))
(setq coords (list 
(list 1280.4859 869.29) 
(list 1280.4771 869.29) 
(list 1280.4763 869.3003) 
(list 1280.4737 869.3106) 
(list 1280.4691 869.3208) 
(list 1280.4629 869.3311) 
(list 1280.455 869.3414) 
(list 1280.4458 869.3517) 
(list 1280.4356 869.3619) 
(list 1280.4245 869.3722) 
(list 1280.4131 869.3825) 
(list 1280.4015 869.3928) 
(list 1280.3902 869.4031) 
(list 1280.3796 869.4133) 
(list 1280.3698 869.4236) 
(list 1280.3613 869.4339) 
(list 1280.3544 869.4442) 
(list 1280.3491 869.4544) 
(list 1280.3458 869.4647) 
(list 1280.3445 869.475) 
(list 1280.3453 869.4853) 
(list 1280.3481 869.4956) 
(list 1280.353 869.5058) 
(list 1280.3597 869.5161) 
(list 1280.3681 869.5264) 
(list 1280.3779 869.5367) 
(list 1280.3889 869.5469) 
(list 1280.4007 869.5572) 
(list 1280.4129 869.5675) 
(list 1280.4253 869.5778) 
(list 1280.4373 869.5881) 
(list 1280.4487 869.5983) 
(list 1280.4591 869.6086) 
(list 1280.4681 869.6189) 
(list 1280.4755 869.6292) 
(list 1280.4811 869.6394) 
(list 1280.4846 869.6497) 
(list 1280.4859 869.66) 
(list 1280.4859 869.66)))
(apply 'command (append '("pline") coords '("c")))
(setq tap4 (ssadd (entlast) tap4))
(command "_mirror" (entlast) "" "1280,900" "1280,901" "No")
(setq tap4 (ssadd (entlast) tap4))
(setq coords (list 
(list 1281.096 869.29) 
(list 1280.4859 869.29) 
(list 1280.4859 869.3003) 
(list 1280.4859 869.3106) 
(list 1280.4859 869.3208) 
(list 1280.4859 869.3311) 
(list 1280.4859 869.3414) 
(list 1280.4859 869.3517) 
(list 1280.4859 869.3619) 
(list 1280.4859 869.3722) 
(list 1280.4859 869.3825) 
(list 1280.4859 869.3928) 
(list 1280.4859 869.4031) 
(list 1280.4859 869.4133) 
(list 1280.4859 869.4236) 
(list 1280.4859 869.4339) 
(list 1280.4859 869.4442) 
(list 1280.4859 869.4544) 
(list 1280.4859 869.4647) 
(list 1280.4859 869.475) 
(list 1280.4859 869.4853) 
(list 1280.4859 869.4956) 
(list 1280.4859 869.5058) 
(list 1280.4859 869.5161) 
(list 1280.4859 869.5264) 
(list 1280.4859 869.5367) 
(list 1280.4859 869.5469) 
(list 1280.4859 869.5572) 
(list 1280.4859 869.5675) 
(list 1280.4859 869.5778) 
(list 1280.4859 869.5881) 
(list 1280.4859 869.5983) 
(list 1280.4859 869.6086) 
(list 1280.4859 869.6189) 
(list 1280.4859 869.6292) 
(list 1280.4859 869.6394) 
(list 1280.4859 869.6497) 
(list 1280.4859 869.66) 
(list 1281.096 869.66)))
(apply 'command (append '("pline") coords '("c")))
(setq tap4 (ssadd (entlast) tap4))
(command "_mirror" (entlast) "" "1280,900" "1280,901" "No")
(setq tap4 (ssadd (entlast) tap4))
(setq coords (list 
(list 1280 869.66) 
(list 1280.135 869.66) 
(list 1280.135 869.6703) 
(list 1280.135 869.6806) 
(list 1280.135 869.6908) 
(list 1280.135 869.7011) 
(list 1280.135 869.7114) 
(list 1280.135 869.7217) 
(list 1280.135 869.7319) 
(list 1280.135 869.7422) 
(list 1280.135 869.7525) 
(list 1280.135 869.7628) 
(list 1280.135 869.7731) 
(list 1280.135 869.7833) 
(list 1280.135 869.7936) 
(list 1280.135 869.8039) 
(list 1280.135 869.8142) 
(list 1280.135 869.8244) 
(list 1280.135 869.8347) 
(list 1280.135 869.845) 
(list 1280.135 869.8553) 
(list 1280.135 869.8656) 
(list 1280.135 869.8758) 
(list 1280.135 869.8861) 
(list 1280.135 869.8964) 
(list 1280.135 869.9067) 
(list 1280.135 869.9169) 
(list 1280.135 869.9272) 
(list 1280.135 869.9375) 
(list 1280.135 869.9478) 
(list 1280.135 869.9581) 
(list 1280.135 869.9683) 
(list 1280.135 869.9786) 
(list 1280.135 869.9889) 
(list 1280.135 869.9992) 
(list 1280.135 870.0094) 
(list 1280.135 870.0197) 
(list 1280.135 870.03) 
(list 1280 870.03)))
(apply 'command (append '("pline") coords '("c")))
(setq tap4 (ssadd (entlast) tap4))
(command "_mirror" (entlast) "" "1280,900" "1280,901" "No")
(setq tap4 (ssadd (entlast) tap4))
(setq coords (list 
(list 1280.4948 869.66) 
(list 1280.4859 869.66) 
(list 1280.4851 869.6703) 
(list 1280.482 869.6806) 
(list 1280.4768 869.6908) 
(list 1280.4696 869.7011) 
(list 1280.4606 869.7114) 
(list 1280.4501 869.7217) 
(list 1280.4384 869.7319) 
(list 1280.4258 869.7422) 
(list 1280.4128 869.7525) 
(list 1280.3997 869.7628) 
(list 1280.3868 869.7731) 
(list 1280.3747 869.7833) 
(list 1280.3637 869.7936) 
(list 1280.3541 869.8039) 
(list 1280.3462 869.8142) 
(list 1280.3403 869.8244) 
(list 1280.3365 869.8347) 
(list 1280.3351 869.845) 
(list 1280.336 869.8553) 
(list 1280.3393 869.8656) 
(list 1280.3448 869.8758) 
(list 1280.3525 869.8861) 
(list 1280.362 869.8964) 
(list 1280.3731 869.9067) 
(list 1280.3855 869.9169) 
(list 1280.3988 869.9272) 
(list 1280.4127 869.9375) 
(list 1280.4266 869.9478) 
(list 1280.4402 869.9581) 
(list 1280.453 869.9683) 
(list 1280.4647 869.9786) 
(list 1280.4748 869.9889) 
(list 1280.4832 869.9992) 
(list 1280.4894 870.0094) 
(list 1280.4933 870.0197) 
(list 1280.4948 870.03) 
(list 1280.4948 870.03)))
(apply 'command (append '("pline") coords '("c")))
(setq tap4 (ssadd (entlast) tap4))
(command "_mirror" (entlast) "" "1280,900" "1280,901" "No")
(setq tap4 (ssadd (entlast) tap4))
(setq coords (list 
(list 1281.096 869.66) 
(list 1280.4948 869.66) 
(list 1280.4948 869.6703) 
(list 1280.4948 869.6806) 
(list 1280.4948 869.6908) 
(list 1280.4948 869.7011) 
(list 1280.4948 869.7114) 
(list 1280.4948 869.7217) 
(list 1280.4948 869.7319) 
(list 1280.4948 869.7422) 
(list 1280.4948 869.7525) 
(list 1280.4948 869.7628) 
(list 1280.4948 869.7731) 
(list 1280.4948 869.7833) 
(list 1280.4948 869.7936) 
(list 1280.4948 869.8039) 
(list 1280.4948 869.8142) 
(list 1280.4948 869.8244) 
(list 1280.4948 869.8347) 
(list 1280.4948 869.845) 
(list 1280.4948 869.8553) 
(list 1280.4948 869.8656) 
(list 1280.4948 869.8758) 
(list 1280.4948 869.8861) 
(list 1280.4948 869.8964) 
(list 1280.4948 869.9067) 
(list 1280.4948 869.9169) 
(list 1280.4948 869.9272) 
(list 1280.4948 869.9375) 
(list 1280.4948 869.9478) 
(list 1280.4948 869.9581) 
(list 1280.4948 869.9683) 
(list 1280.4948 869.9786) 
(list 1280.4948 869.9889) 
(list 1280.4948 869.9992) 
(list 1280.4948 870.0094) 
(list 1280.4948 870.0197) 
(list 1280.4948 870.03) 
(list 1281.096 870.03)))
(apply 'command (append '("pline") coords '("c")))
(setq tap4 (ssadd (entlast) tap4))
(command "_mirror" (entlast) "" "1280,900" "1280,901" "No")
(setq tap4 (ssadd (entlast) tap4))
(setq coords (list 
(list 1280 870.03) 
(list 1280.135 870.03) 
(list 1280.135 870.0403) 
(list 1280.135 870.0506) 
(list 1280.135 870.0608) 
(list 1280.135 870.0711) 
(list 1280.135 870.0814) 
(list 1280.135 870.0917) 
(list 1280.135 870.1019) 
(list 1280.135 870.1122) 
(list 1280.135 870.1225) 
(list 1280.135 870.1328) 
(list 1280.135 870.1431) 
(list 1280.135 870.1533) 
(list 1280.135 870.1636) 
(list 1280.135 870.1739) 
(list 1280.135 870.1842) 
(list 1280.135 870.1944) 
(list 1280.135 870.2047) 
(list 1280.135 870.215) 
(list 1280.135 870.2253) 
(list 1280.135 870.2356) 
(list 1280.135 870.2458) 
(list 1280.135 870.2561) 
(list 1280.135 870.2664) 
(list 1280.135 870.2767) 
(list 1280.135 870.2869) 
(list 1280.135 870.2972) 
(list 1280.135 870.3075) 
(list 1280.135 870.3178) 
(list 1280.135 870.3281) 
(list 1280.135 870.3383) 
(list 1280.135 870.3486) 
(list 1280.135 870.3589) 
(list 1280.135 870.3692) 
(list 1280.135 870.3794) 
(list 1280.135 870.3897) 
(list 1280.135 870.4) 
(list 1280 870.4)))
(apply 'command (append '("pline") coords '("c")))
(setq tap4 (ssadd (entlast) tap4))
(command "_mirror" (entlast) "" "1280,900" "1280,901" "No")
(setq tap4 (ssadd (entlast) tap4))
(setq coords (list 
(list 1280.5037 870.03) 
(list 1280.4948 870.03) 
(list 1280.4938 870.0403) 
(list 1280.4903 870.0506) 
(list 1280.4844 870.0608) 
(list 1280.4763 870.0711) 
(list 1280.4662 870.0814) 
(list 1280.4544 870.0917) 
(list 1280.4413 870.1019) 
(list 1280.4272 870.1122) 
(list 1280.4125 870.1225) 
(list 1280.3978 870.1328) 
(list 1280.3835 870.1431) 
(list 1280.3699 870.1533) 
(list 1280.3575 870.1636) 
(list 1280.3468 870.1739) 
(list 1280.338 870.1842) 
(list 1280.3314 870.1944) 
(list 1280.3273 870.2047) 
(list 1280.3257 870.215) 
(list 1280.3268 870.2253) 
(list 1280.3304 870.2356) 
(list 1280.3366 870.2458) 
(list 1280.3452 870.2561) 
(list 1280.3558 870.2664) 
(list 1280.3683 870.2767) 
(list 1280.3821 870.2869) 
(list 1280.397 870.2972) 
(list 1280.4124 870.3075) 
(list 1280.4279 870.3178) 
(list 1280.443 870.3281) 
(list 1280.4573 870.3383) 
(list 1280.4703 870.3486) 
(list 1280.4816 870.3589) 
(list 1280.4908 870.3692) 
(list 1280.4977 870.3794) 
(list 1280.502 870.3897) 
(list 1280.5037 870.4) 
(list 1280.5037 870.4)))
(apply 'command (append '("pline") coords '("c")))
(setq tap4 (ssadd (entlast) tap4))
(command "_mirror" (entlast) "" "1280,900" "1280,901" "No")
(setq tap4 (ssadd (entlast) tap4))
(setq coords (list 
(list 1281.096 870.03) 
(list 1280.5037 870.03) 
(list 1280.5037 870.0403) 
(list 1280.5037 870.0506) 
(list 1280.5037 870.0608) 
(list 1280.5037 870.0711) 
(list 1280.5037 870.0814) 
(list 1280.5037 870.0917) 
(list 1280.5037 870.1019) 
(list 1280.5037 870.1122) 
(list 1280.5037 870.1225) 
(list 1280.5037 870.1328) 
(list 1280.5037 870.1431) 
(list 1280.5037 870.1533) 
(list 1280.5037 870.1636) 
(list 1280.5037 870.1739) 
(list 1280.5037 870.1842) 
(list 1280.5037 870.1944) 
(list 1280.5037 870.2047) 
(list 1280.5037 870.215) 
(list 1280.5037 870.2253) 
(list 1280.5037 870.2356) 
(list 1280.5037 870.2458) 
(list 1280.5037 870.2561) 
(list 1280.5037 870.2664) 
(list 1280.5037 870.2767) 
(list 1280.5037 870.2869) 
(list 1280.5037 870.2972) 
(list 1280.5037 870.3075) 
(list 1280.5037 870.3178) 
(list 1280.5037 870.3281) 
(list 1280.5037 870.3383) 
(list 1280.5037 870.3486) 
(list 1280.5037 870.3589) 
(list 1280.5037 870.3692) 
(list 1280.5037 870.3794) 
(list 1280.5037 870.3897) 
(list 1280.5037 870.4) 
(list 1281.096 870.4)))
(apply 'command (append '("pline") coords '("c")))
(setq tap4 (ssadd (entlast) tap4))
(command "_mirror" (entlast) "" "1280,900" "1280,901" "No")
(setq tap4 (ssadd (entlast) tap4))
(setq coords (list 
(list 1280 870.4) 
(list 1280.135 870.4) 
(list 1280.135 870.4103) 
(list 1280.135 870.4206) 
(list 1280.135 870.4308) 
(list 1280.135 870.4411) 
(list 1280.135 870.4514) 
(list 1280.135 870.4617) 
(list 1280.135 870.4719) 
(list 1280.135 870.4822) 
(list 1280.135 870.4925) 
(list 1280.135 870.5028) 
(list 1280.135 870.5131) 
(list 1280.135 870.5233) 
(list 1280.135 870.5336) 
(list 1280.135 870.5439) 
(list 1280.135 870.5542) 
(list 1280.135 870.5644) 
(list 1280.135 870.5747) 
(list 1280.135 870.585) 
(list 1280.135 870.5953) 
(list 1280.135 870.6056) 
(list 1280.135 870.6158) 
(list 1280.135 870.6261) 
(list 1280.135 870.6364) 
(list 1280.135 870.6467) 
(list 1280.135 870.6569) 
(list 1280.135 870.6672) 
(list 1280.135 870.6775) 
(list 1280.135 870.6878) 
(list 1280.135 870.6981) 
(list 1280.135 870.7083) 
(list 1280.135 870.7186) 
(list 1280.135 870.7289) 
(list 1280.135 870.7392) 
(list 1280.135 870.7494) 
(list 1280.135 870.7597) 
(list 1280.135 870.77) 
(list 1280 870.77)))
(apply 'command (append '("pline") coords '("c")))
(setq tap4 (ssadd (entlast) tap4))
(command "_mirror" (entlast) "" "1280,900" "1280,901" "No")
(setq tap4 (ssadd (entlast) tap4))
(setq coords (list 
(list 1280.5125 870.4) 
(list 1280.5037 870.4) 
(list 1280.5025 870.4103) 
(list 1280.4986 870.4206) 
(list 1280.4921 870.4308) 
(list 1280.483 870.4411) 
(list 1280.4718 870.4514) 
(list 1280.4587 870.4617) 
(list 1280.4441 870.4719) 
(list 1280.4285 870.4822) 
(list 1280.4123 870.4925) 
(list 1280.396 870.5028) 
(list 1280.3801 870.5131) 
(list 1280.3651 870.5233) 
(list 1280.3514 870.5336) 
(list 1280.3395 870.5439) 
(list 1280.3298 870.5542) 
(list 1280.3226 870.5644) 
(list 1280.318 870.5747) 
(list 1280.3163 870.585) 
(list 1280.3175 870.5953) 
(list 1280.3216 870.6056) 
(list 1280.3285 870.6158) 
(list 1280.3379 870.6261) 
(list 1280.3497 870.6364) 
(list 1280.3634 870.6467) 
(list 1280.3787 870.6569) 
(list 1280.3951 870.6672) 
(list 1280.4121 870.6775) 
(list 1280.4292 870.6878) 
(list 1280.4459 870.6981) 
(list 1280.4616 870.7083) 
(list 1280.4759 870.7186) 
(list 1280.4883 870.7289) 
(list 1280.4984 870.7392) 
(list 1280.506 870.7494) 
(list 1280.5108 870.7597) 
(list 1280.5125 870.77) 
(list 1280.5125 870.77)))
(apply 'command (append '("pline") coords '("c")))
(setq tap4 (ssadd (entlast) tap4))
(command "_mirror" (entlast) "" "1280,900" "1280,901" "No")
(setq tap4 (ssadd (entlast) tap4))
(setq coords (list 
(list 1281.096 870.4) 
(list 1280.5125 870.4) 
(list 1280.5125 870.4103) 
(list 1280.5125 870.4206) 
(list 1280.5125 870.4308) 
(list 1280.5125 870.4411) 
(list 1280.5125 870.4514) 
(list 1280.5125 870.4617) 
(list 1280.5125 870.4719) 
(list 1280.5125 870.4822) 
(list 1280.5125 870.4925) 
(list 1280.5125 870.5028) 
(list 1280.5125 870.5131) 
(list 1280.5125 870.5233) 
(list 1280.5125 870.5336) 
(list 1280.5125 870.5439) 
(list 1280.5125 870.5542) 
(list 1280.5125 870.5644) 
(list 1280.5125 870.5747) 
(list 1280.5125 870.585) 
(list 1280.5125 870.5953) 
(list 1280.5125 870.6056) 
(list 1280.5125 870.6158) 
(list 1280.5125 870.6261) 
(list 1280.5125 870.6364) 
(list 1280.5125 870.6467) 
(list 1280.5125 870.6569) 
(list 1280.5125 870.6672) 
(list 1280.5125 870.6775) 
(list 1280.5125 870.6878) 
(list 1280.5125 870.6981) 
(list 1280.5125 870.7083) 
(list 1280.5125 870.7186) 
(list 1280.5125 870.7289) 
(list 1280.5125 870.7392) 
(list 1280.5125 870.7494) 
(list 1280.5125 870.7597) 
(list 1280.5125 870.77) 
(list 1281.096 870.77)))
(apply 'command (append '("pline") coords '("c")))
(setq tap4 (ssadd (entlast) tap4))
(command "_mirror" (entlast) "" "1280,900" "1280,901" "No")
(setq tap4 (ssadd (entlast) tap4))
(setq coords (list 
(list 1280 870.77) 
(list 1280.135 870.77) 
(list 1280.135 870.7803) 
(list 1280.135 870.7906) 
(list 1280.135 870.8008) 
(list 1280.135 870.8111) 
(list 1280.135 870.8214) 
(list 1280.135 870.8317) 
(list 1280.135 870.8419) 
(list 1280.135 870.8522) 
(list 1280.135 870.8625) 
(list 1280.135 870.8728) 
(list 1280.135 870.8831) 
(list 1280.135 870.8933) 
(list 1280.135 870.9036) 
(list 1280.135 870.9139) 
(list 1280.135 870.9242) 
(list 1280.135 870.9344) 
(list 1280.135 870.9447) 
(list 1280.135 870.955) 
(list 1280.135 870.9653) 
(list 1280.135 870.9756) 
(list 1280.135 870.9858) 
(list 1280.135 870.9961) 
(list 1280.135 871.0064) 
(list 1280.135 871.0167) 
(list 1280.135 871.0269) 
(list 1280.135 871.0372) 
(list 1280.135 871.0475) 
(list 1280.135 871.0578) 
(list 1280.135 871.0681) 
(list 1280.135 871.0783) 
(list 1280.135 871.0886) 
(list 1280.135 871.0989) 
(list 1280.135 871.1092) 
(list 1280.135 871.1194) 
(list 1280.135 871.1297) 
(list 1280.135 871.14) 
(list 1280 871.14)))
(apply 'command (append '("pline") coords '("c")))
(setq tap4 (ssadd (entlast) tap4))
(command "_mirror" (entlast) "" "1280,900" "1280,901" "No")
(setq tap4 (ssadd (entlast) tap4))
(setq coords (list 
(list 1280.5214 870.77) 
(list 1280.5125 870.77) 
(list 1280.5112 870.7803) 
(list 1280.5069 870.7906) 
(list 1280.4997 870.8008) 
(list 1280.4898 870.8111) 
(list 1280.4774 870.8214) 
(list 1280.463 870.8317) 
(list 1280.447 870.8419) 
(list 1280.4298 870.8522) 
(list 1280.412 870.8625) 
(list 1280.3941 870.8728) 
(list 1280.3767 870.8831) 
(list 1280.3602 870.8933) 
(list 1280.3453 870.9036) 
(list 1280.3323 870.9139) 
(list 1280.3217 870.9242) 
(list 1280.3137 870.9344) 
(list 1280.3088 870.9447) 
(list 1280.3069 870.955) 
(list 1280.3082 870.9653) 
(list 1280.3127 870.9756) 
(list 1280.3203 870.9858) 
(list 1280.3307 870.9961) 
(list 1280.3436 871.0064) 
(list 1280.3586 871.0167) 
(list 1280.3754 871.0269) 
(list 1280.3933 871.0372) 
(list 1280.4119 871.0475) 
(list 1280.4305 871.0578) 
(list 1280.4487 871.0681) 
(list 1280.4659 871.0783) 
(list 1280.4815 871.0886) 
(list 1280.495 871.0989) 
(list 1280.5061 871.1092) 
(list 1280.5143 871.1194) 
(list 1280.5195 871.1297) 
(list 1280.5214 871.14) 
(list 1280.5214 871.14)))
(apply 'command (append '("pline") coords '("c")))
(setq tap4 (ssadd (entlast) tap4))
(command "_mirror" (entlast) "" "1280,900" "1280,901" "No")
(setq tap4 (ssadd (entlast) tap4))
(setq coords (list 
(list 1281.096 870.77) 
(list 1280.5214 870.77) 
(list 1280.5214 870.7803) 
(list 1280.5214 870.7906) 
(list 1280.5214 870.8008) 
(list 1280.5214 870.8111) 
(list 1280.5214 870.8214) 
(list 1280.5214 870.8317) 
(list 1280.5214 870.8419) 
(list 1280.5214 870.8522) 
(list 1280.5214 870.8625) 
(list 1280.5214 870.8728) 
(list 1280.5214 870.8831) 
(list 1280.5214 870.8933) 
(list 1280.5214 870.9036) 
(list 1280.5214 870.9139) 
(list 1280.5214 870.9242) 
(list 1280.5214 870.9344) 
(list 1280.5214 870.9447) 
(list 1280.5214 870.955) 
(list 1280.5214 870.9653) 
(list 1280.5214 870.9756) 
(list 1280.5214 870.9858) 
(list 1280.5214 870.9961) 
(list 1280.5214 871.0064) 
(list 1280.5214 871.0167) 
(list 1280.5214 871.0269) 
(list 1280.5214 871.0372) 
(list 1280.5214 871.0475) 
(list 1280.5214 871.0578) 
(list 1280.5214 871.0681) 
(list 1280.5214 871.0783) 
(list 1280.5214 871.0886) 
(list 1280.5214 871.0989) 
(list 1280.5214 871.1092) 
(list 1280.5214 871.1194) 
(list 1280.5214 871.1297) 
(list 1280.5214 871.14) 
(list 1281.096 871.14)))
(apply 'command (append '("pline") coords '("c")))
(setq tap4 (ssadd (entlast) tap4))
(command "_mirror" (entlast) "" "1280,900" "1280,901" "No")
(setq tap4 (ssadd (entlast) tap4))
(setq coords (list 
(list 1280 871.14) 
(list 1280.135 871.14) 
(list 1280.135 871.1503) 
(list 1280.135 871.1606) 
(list 1280.135 871.1708) 
(list 1280.135 871.1811) 
(list 1280.135 871.1914) 
(list 1280.135 871.2017) 
(list 1280.135 871.2119) 
(list 1280.135 871.2222) 
(list 1280.135 871.2325) 
(list 1280.135 871.2428) 
(list 1280.135 871.2531) 
(list 1280.135 871.2633) 
(list 1280.135 871.2736) 
(list 1280.135 871.2839) 
(list 1280.135 871.2942) 
(list 1280.135 871.3044) 
(list 1280.135 871.3147) 
(list 1280.135 871.325) 
(list 1280.135 871.3353) 
(list 1280.135 871.3456) 
(list 1280.135 871.3558) 
(list 1280.135 871.3661) 
(list 1280.135 871.3764) 
(list 1280.135 871.3867) 
(list 1280.135 871.3969) 
(list 1280.135 871.4072) 
(list 1280.135 871.4175) 
(list 1280.135 871.4278) 
(list 1280.135 871.4381) 
(list 1280.135 871.4483) 
(list 1280.135 871.4586) 
(list 1280.135 871.4689) 
(list 1280.135 871.4792) 
(list 1280.135 871.4894) 
(list 1280.135 871.4997) 
(list 1280.135 871.51) 
(list 1280 871.51)))
(apply 'command (append '("pline") coords '("c")))
(setq tap4 (ssadd (entlast) tap4))
(command "_mirror" (entlast) "" "1280,900" "1280,901" "No")
(setq tap4 (ssadd (entlast) tap4))
(setq coords (list 
(list 1280.5303 871.14) 
(list 1280.5214 871.14) 
(list 1280.52 871.1503) 
(list 1280.5153 871.1606) 
(list 1280.5074 871.1708) 
(list 1280.4965 871.1811) 
(list 1280.483 871.1914) 
(list 1280.4673 871.2017) 
(list 1280.4498 871.2119) 
(list 1280.4311 871.2222) 
(list 1280.4117 871.2325) 
(list 1280.3923 871.2428) 
(list 1280.3733 871.2531) 
(list 1280.3554 871.2633) 
(list 1280.3391 871.2736) 
(list 1280.325 871.2839) 
(list 1280.3135 871.2942) 
(list 1280.3049 871.3044) 
(list 1280.2995 871.3147) 
(list 1280.2975 871.325) 
(list 1280.299 871.3353) 
(list 1280.3039 871.3456) 
(list 1280.3121 871.3558) 
(list 1280.3234 871.3661) 
(list 1280.3374 871.3764) 
(list 1280.3538 871.3867) 
(list 1280.372 871.3969) 
(list 1280.3914 871.4072) 
(list 1280.4116 871.4175) 
(list 1280.4319 871.4278) 
(list 1280.4516 871.4381) 
(list 1280.4702 871.4483) 
(list 1280.4871 871.4586) 
(list 1280.5017 871.4689) 
(list 1280.5137 871.4792) 
(list 1280.5226 871.4894) 
(list 1280.5282 871.4997) 
(list 1280.5303 871.51) 
(list 1280.5303 871.51)))
(apply 'command (append '("pline") coords '("c")))
(setq tap4 (ssadd (entlast) tap4))
(command "_mirror" (entlast) "" "1280,900" "1280,901" "No")
(setq tap4 (ssadd (entlast) tap4))
(setq coords (list 
(list 1281.096 871.14) 
(list 1280.5303 871.14) 
(list 1280.5303 871.1503) 
(list 1280.5303 871.1606) 
(list 1280.5303 871.1708) 
(list 1280.5303 871.1811) 
(list 1280.5303 871.1914) 
(list 1280.5303 871.2017) 
(list 1280.5303 871.2119) 
(list 1280.5303 871.2222) 
(list 1280.5303 871.2325) 
(list 1280.5303 871.2428) 
(list 1280.5303 871.2531) 
(list 1280.5303 871.2633) 
(list 1280.5303 871.2736) 
(list 1280.5303 871.2839) 
(list 1280.5303 871.2942) 
(list 1280.5303 871.3044) 
(list 1280.5303 871.3147) 
(list 1280.5303 871.325) 
(list 1280.5303 871.3353) 
(list 1280.5303 871.3456) 
(list 1280.5303 871.3558) 
(list 1280.5303 871.3661) 
(list 1280.5303 871.3764) 
(list 1280.5303 871.3867) 
(list 1280.5303 871.3969) 
(list 1280.5303 871.4072) 
(list 1280.5303 871.4175) 
(list 1280.5303 871.4278) 
(list 1280.5303 871.4381) 
(list 1280.5303 871.4483) 
(list 1280.5303 871.4586) 
(list 1280.5303 871.4689) 
(list 1280.5303 871.4792) 
(list 1280.5303 871.4894) 
(list 1280.5303 871.4997) 
(list 1280.5303 871.51) 
(list 1281.096 871.51)))
(apply 'command (append '("pline") coords '("c")))
(setq tap4 (ssadd (entlast) tap4))
(command "_mirror" (entlast) "" "1280,900" "1280,901" "No")
(setq tap4 (ssadd (entlast) tap4))
(setq coords (list 
(list 1280 871.51) 
(list 1280.135 871.51) 
(list 1280.135 871.5203) 
(list 1280.135 871.5306) 
(list 1280.135 871.5408) 
(list 1280.135 871.5511) 
(list 1280.135 871.5614) 
(list 1280.135 871.5717) 
(list 1280.135 871.5819) 
(list 1280.135 871.5922) 
(list 1280.135 871.6025) 
(list 1280.135 871.6128) 
(list 1280.135 871.6231) 
(list 1280.135 871.6333) 
(list 1280.135 871.6436) 
(list 1280.135 871.6539) 
(list 1280.135 871.6642) 
(list 1280.135 871.6744) 
(list 1280.135 871.6847) 
(list 1280.135 871.695) 
(list 1280.135 871.7053) 
(list 1280.135 871.7156) 
(list 1280.135 871.7258) 
(list 1280.135 871.7361) 
(list 1280.135 871.7464) 
(list 1280.135 871.7567) 
(list 1280.135 871.7669) 
(list 1280.135 871.7772) 
(list 1280.135 871.7875) 
(list 1280.135 871.7978) 
(list 1280.135 871.8081) 
(list 1280.135 871.8183) 
(list 1280.135 871.8286) 
(list 1280.135 871.8389) 
(list 1280.135 871.8492) 
(list 1280.135 871.8594) 
(list 1280.135 871.8697) 
(list 1280.135 871.88) 
(list 1280 871.88)))
(apply 'command (append '("pline") coords '("c")))
(setq tap4 (ssadd (entlast) tap4))
(command "_mirror" (entlast) "" "1280,900" "1280,901" "No")
(setq tap4 (ssadd (entlast) tap4))
(setq coords (list 
(list 1280.5391 871.51) 
(list 1280.5303 871.51) 
(list 1280.5287 871.5203) 
(list 1280.5236 871.5306) 
(list 1280.515 871.5408) 
(list 1280.5032 871.5511) 
(list 1280.4886 871.5614) 
(list 1280.4716 871.5717) 
(list 1280.4527 871.5819) 
(list 1280.4324 871.5922) 
(list 1280.4115 871.6025) 
(list 1280.3904 871.6128) 
(list 1280.3699 871.6231) 
(list 1280.3506 871.6333) 
(list 1280.333 871.6436) 
(list 1280.3178 871.6539) 
(list 1280.3053 871.6642) 
(list 1280.296 871.6744) 
(list 1280.2902 871.6847) 
(list 1280.2881 871.695) 
(list 1280.2897 871.7053) 
(list 1280.295 871.7156) 
(list 1280.3039 871.7258) 
(list 1280.3161 871.7361) 
(list 1280.3313 871.7464) 
(list 1280.3489 871.7567) 
(list 1280.3686 871.7669) 
(list 1280.3896 871.7772) 
(list 1280.4113 871.7875) 
(list 1280.4332 871.7978) 
(list 1280.4544 871.8081) 
(list 1280.4745 871.8183) 
(list 1280.4927 871.8286) 
(list 1280.5085 871.8389) 
(list 1280.5214 871.8492) 
(list 1280.531 871.8594) 
(list 1280.5369 871.8697) 
(list 1280.5391 871.88) 
(list 1280.5391 871.88)))
(apply 'command (append '("pline") coords '("c")))
(setq tap4 (ssadd (entlast) tap4))
(command "_mirror" (entlast) "" "1280,900" "1280,901" "No")
(setq tap4 (ssadd (entlast) tap4))
(setq coords (list 
(list 1281.096 871.51) 
(list 1280.5391 871.51) 
(list 1280.5391 871.5203) 
(list 1280.5391 871.5306) 
(list 1280.5391 871.5408) 
(list 1280.5391 871.5511) 
(list 1280.5391 871.5614) 
(list 1280.5391 871.5717) 
(list 1280.5391 871.5819) 
(list 1280.5391 871.5922) 
(list 1280.5391 871.6025) 
(list 1280.5391 871.6128) 
(list 1280.5391 871.6231) 
(list 1280.5391 871.6333) 
(list 1280.5391 871.6436) 
(list 1280.5391 871.6539) 
(list 1280.5391 871.6642) 
(list 1280.5391 871.6744) 
(list 1280.5391 871.6847) 
(list 1280.5391 871.695) 
(list 1280.5391 871.7053) 
(list 1280.5391 871.7156) 
(list 1280.5391 871.7258) 
(list 1280.5391 871.7361) 
(list 1280.5391 871.7464) 
(list 1280.5391 871.7567) 
(list 1280.5391 871.7669) 
(list 1280.5391 871.7772) 
(list 1280.5391 871.7875) 
(list 1280.5391 871.7978) 
(list 1280.5391 871.8081) 
(list 1280.5391 871.8183) 
(list 1280.5391 871.8286) 
(list 1280.5391 871.8389) 
(list 1280.5391 871.8492) 
(list 1280.5391 871.8594) 
(list 1280.5391 871.8697) 
(list 1280.5391 871.88) 
(list 1281.096 871.88)))
(apply 'command (append '("pline") coords '("c")))
(setq tap4 (ssadd (entlast) tap4))
(command "_mirror" (entlast) "" "1280,900" "1280,901" "No")
(setq tap4 (ssadd (entlast) tap4))
(setq coords (list 
(list 1280 871.88) 
(list 1280.135 871.88) 
(list 1280.135 871.8903) 
(list 1280.135 871.9006) 
(list 1280.135 871.9108) 
(list 1280.135 871.9211) 
(list 1280.135 871.9314) 
(list 1280.135 871.9417) 
(list 1280.135 871.9519) 
(list 1280.135 871.9622) 
(list 1280.135 871.9725) 
(list 1280.135 871.9828) 
(list 1280.135 871.9931) 
(list 1280.135 872.0033) 
(list 1280.135 872.0136) 
(list 1280.135 872.0239) 
(list 1280.135 872.0342) 
(list 1280.135 872.0444) 
(list 1280.135 872.0547) 
(list 1280.135 872.065) 
(list 1280.135 872.0753) 
(list 1280.135 872.0856) 
(list 1280.135 872.0958) 
(list 1280.135 872.1061) 
(list 1280.135 872.1164) 
(list 1280.135 872.1267) 
(list 1280.135 872.1369) 
(list 1280.135 872.1472) 
(list 1280.135 872.1575) 
(list 1280.135 872.1678) 
(list 1280.135 872.1781) 
(list 1280.135 872.1883) 
(list 1280.135 872.1986) 
(list 1280.135 872.2089) 
(list 1280.135 872.2192) 
(list 1280.135 872.2294) 
(list 1280.135 872.2397) 
(list 1280.135 872.25) 
(list 1280 872.25)))
(apply 'command (append '("pline") coords '("c")))
(setq tap4 (ssadd (entlast) tap4))
(command "_mirror" (entlast) "" "1280,900" "1280,901" "No")
(setq tap4 (ssadd (entlast) tap4))
(setq coords (list 
(list 1280.548 871.88) 
(list 1280.5391 871.88) 
(list 1280.5374 871.8903) 
(list 1280.5319 871.9006) 
(list 1280.5226 871.9108) 
(list 1280.51 871.9211) 
(list 1280.4942 871.9314) 
(list 1280.4759 871.9417) 
(list 1280.4556 871.9519) 
(list 1280.4338 871.9622) 
(list 1280.4112 871.9725) 
(list 1280.3885 871.9828) 
(list 1280.3665 871.9931) 
(list 1280.3457 872.0033) 
(list 1280.3269 872.0136) 
(list 1280.3105 872.0239) 
(list 1280.2971 872.0342) 
(list 1280.2872 872.0444) 
(list 1280.281 872.0547) 
(list 1280.2787 872.065) 
(list 1280.2805 872.0753) 
(list 1280.2862 872.0856) 
(list 1280.2958 872.0958) 
(list 1280.3089 872.1061) 
(list 1280.3252 872.1164) 
(list 1280.3441 872.1267) 
(list 1280.3652 872.1369) 
(list 1280.3877 872.1472) 
(list 1280.4111 872.1575) 
(list 1280.4345 872.1678) 
(list 1280.4573 872.1781) 
(list 1280.4788 872.1883) 
(list 1280.4983 872.1986) 
(list 1280.5152 872.2089) 
(list 1280.529 872.2192) 
(list 1280.5393 872.2294) 
(list 1280.5457 872.2397) 
(list 1280.548 872.25) 
(list 1280.548 872.25)))
(apply 'command (append '("pline") coords '("c")))
(setq tap4 (ssadd (entlast) tap4))
(command "_mirror" (entlast) "" "1280,900" "1280,901" "No")
(setq tap4 (ssadd (entlast) tap4))
(setq coords (list 
(list 1281.096 871.88) 
(list 1280.548 871.88) 
(list 1280.548 871.8903) 
(list 1280.548 871.9006) 
(list 1280.548 871.9108) 
(list 1280.548 871.9211) 
(list 1280.548 871.9314) 
(list 1280.548 871.9417) 
(list 1280.548 871.9519) 
(list 1280.548 871.9622) 
(list 1280.548 871.9725) 
(list 1280.548 871.9828) 
(list 1280.548 871.9931) 
(list 1280.548 872.0033) 
(list 1280.548 872.0136) 
(list 1280.548 872.0239) 
(list 1280.548 872.0342) 
(list 1280.548 872.0444) 
(list 1280.548 872.0547) 
(list 1280.548 872.065) 
(list 1280.548 872.0753) 
(list 1280.548 872.0856) 
(list 1280.548 872.0958) 
(list 1280.548 872.1061) 
(list 1280.548 872.1164) 
(list 1280.548 872.1267) 
(list 1280.548 872.1369) 
(list 1280.548 872.1472) 
(list 1280.548 872.1575) 
(list 1280.548 872.1678) 
(list 1280.548 872.1781) 
(list 1280.548 872.1883) 
(list 1280.548 872.1986) 
(list 1280.548 872.2089) 
(list 1280.548 872.2192) 
(list 1280.548 872.2294) 
(list 1280.548 872.2397) 
(list 1280.548 872.25) 
(list 1281.096 872.25)))
(apply 'command (append '("pline") coords '("c")))
(setq tap4 (ssadd (entlast) tap4))
(command "_mirror" (entlast) "" "1280,900" "1280,901" "No")
(setq tap4 (ssadd (entlast) tap4))
(command "_block" "blktap4" "1280,900" tap4 "")
(command "_insert" "blktap4" "1280,900" "1" "1" "0")
(command "_insert" "blktap4" "1280,900" "1" "1" "180")
(setq uc4 nil)
(setq uc4 (ssadd))
(setq coords (list 
(list 0 -0.185) 
(list 0.135 -0.185) 
(list 0.135 -0.17472) 
(list 0.135 -0.16444) 
(list 0.135 -0.15417) 
(list 0.135 -0.14389) 
(list 0.135 -0.13361) 
(list 0.135 -0.12333) 
(list 0.135 -0.11306) 
(list 0.135 -0.10278) 
(list 0.135 -0.0925) 
(list 0.135 -0.082222) 
(list 0.135 -0.071944) 
(list 0.135 -0.061667) 
(list 0.135 -0.051389) 
(list 0.135 -0.041111) 
(list 0.135 -0.030833) 
(list 0.135 -0.020556) 
(list 0.135 -0.010278) 
(list 0.135 0) 
(list 0.135 0.010278) 
(list 0.135 0.020556) 
(list 0.135 0.030833) 
(list 0.135 0.041111) 
(list 0.135 0.051389) 
(list 0.135 0.061667) 
(list 0.135 0.071944) 
(list 0.135 0.082222) 
(list 0.135 0.0925) 
(list 0.135 0.10278) 
(list 0.135 0.11306) 
(list 0.135 0.12333) 
(list 0.135 0.13361) 
(list 0.135 0.14389) 
(list 0.135 0.15417) 
(list 0.135 0.16444) 
(list 0.135 0.17472) 
(list 0.135 0.185) 
(list 0 0.185)))
(apply 'command (append '("pline") coords '("c")))
(setq uc4 (ssadd (entlast) uc4))
(setq coords (list 
(list 1.096 -0.185) 
(list 0.548 -0.185) 
(list 0.54592 -0.17472) 
(list 0.53974 -0.16444) 
(list 0.52965 -0.15417) 
(list 0.51595 -0.14389) 
(list 0.49906 -0.13361) 
(list 0.4795 -0.12333) 
(list 0.45786 -0.11306) 
(list 0.43479 -0.10278) 
(list 0.411 -0.0925) 
(list 0.38721 -0.082222) 
(list 0.36414 -0.071944) 
(list 0.3425 -0.061667) 
(list 0.32294 -0.051389) 
(list 0.30605 -0.041111) 
(list 0.29235 -0.030833) 
(list 0.28226 -0.020556) 
(list 0.27608 -0.010278) 
(list 0.274 0) 
(list 0.27608 0.010278) 
(list 0.28226 0.020556) 
(list 0.29235 0.030833) 
(list 0.30605 0.041111) 
(list 0.32294 0.051389) 
(list 0.3425 0.061667) 
(list 0.36414 0.071944) 
(list 0.38721 0.082222) 
(list 0.411 0.0925) 
(list 0.43479 0.10278) 
(list 0.45786 0.11306) 
(list 0.4795 0.12333) 
(list 0.49906 0.13361) 
(list 0.51595 0.14389) 
(list 0.52965 0.15417) 
(list 0.53974 0.16444) 
(list 0.54592 0.17472) 
(list 0.548 0.185) 
(list 1.096 0.185)))
(apply 'command (append '("pline") coords '("c")))
(setq uc4 (ssadd (entlast) uc4))
(command "_block" "blkuc4" "0,0.185" uc4 "")
(command "_insert" "blkuc4" "1280,872.62" "1" "1" "0")
(command "_insert" "blkuc4" "1280,872.25" "1" "1" "180")
(command "_insert" "blkuc4" "1280,872.99" "1" "1" "0")
(command "_insert" "blkuc4" "1280,872.62" "1" "1" "180")
(command "_insert" "blkuc4" "1280,873.36" "1" "1" "0")
(command "_insert" "blkuc4" "1280,872.99" "1" "1" "180")
(command "_insert" "blkuc4" "1280,873.73" "1" "1" "0")
(command "_insert" "blkuc4" "1280,873.36" "1" "1" "180")
(command "_insert" "blkuc4" "1280,874.1" "1" "1" "0")
(command "_insert" "blkuc4" "1280,873.73" "1" "1" "180")
(command "_insert" "blkuc4" "1280,874.47" "1" "1" "0")
(command "_insert" "blkuc4" "1280,874.1" "1" "1" "180")
(command "_insert" "blkuc4" "1280,874.84" "1" "1" "0")
(command "_insert" "blkuc4" "1280,874.47" "1" "1" "180")
(command "_insert" "blkuc4" "1280,875.21" "1" "1" "0")
(command "_insert" "blkuc4" "1280,874.84" "1" "1" "180")
(command "_insert" "blkuc4" "1280,875.58" "1" "1" "0")
(command "_insert" "blkuc4" "1280,875.21" "1" "1" "180")
(command "_insert" "blkuc4" "1280,875.95" "1" "1" "0")
(command "_insert" "blkuc4" "1280,875.58" "1" "1" "180")
(command "_insert" "blkuc4" "1280,876.32" "1" "1" "0")
(command "_insert" "blkuc4" "1280,875.95" "1" "1" "180")
(command "_insert" "blkuc4" "1280,876.69" "1" "1" "0")
(command "_insert" "blkuc4" "1280,876.32" "1" "1" "180")
(command "_insert" "blkuc4" "1280,877.06" "1" "1" "0")
(command "_insert" "blkuc4" "1280,876.69" "1" "1" "180")
(command "_insert" "blkuc4" "1280,877.43" "1" "1" "0")
(command "_insert" "blkuc4" "1280,877.06" "1" "1" "180")
(command "_insert" "blkuc4" "1280,877.8" "1" "1" "0")
(command "_insert" "blkuc4" "1280,877.43" "1" "1" "180")
(command "_insert" "blkuc4" "1280,878.17" "1" "1" "0")
(command "_insert" "blkuc4" "1280,877.8" "1" "1" "180")
(command "_insert" "blkuc4" "1280,878.54" "1" "1" "0")
(command "_insert" "blkuc4" "1280,878.17" "1" "1" "180")
(command "_insert" "blkuc4" "1280,878.91" "1" "1" "0")
(command "_insert" "blkuc4" "1280,878.54" "1" "1" "180")
(command "_insert" "blkuc4" "1280,879.28" "1" "1" "0")
(command "_insert" "blkuc4" "1280,878.91" "1" "1" "180")
(command "_insert" "blkuc4" "1280,879.65" "1" "1" "0")
(command "_insert" "blkuc4" "1280,879.28" "1" "1" "180")
(command "_insert" "blkuc4" "1280,880.02" "1" "1" "0")
(command "_insert" "blkuc4" "1280,879.65" "1" "1" "180")
(command "_insert" "blkuc4" "1280,880.39" "1" "1" "0")
(command "_insert" "blkuc4" "1280,880.02" "1" "1" "180")
(command "_insert" "blkuc4" "1280,880.76" "1" "1" "0")
(command "_insert" "blkuc4" "1280,880.39" "1" "1" "180")
(command "_insert" "blkuc4" "1280,881.13" "1" "1" "0")
(command "_insert" "blkuc4" "1280,880.76" "1" "1" "180")
(command "_insert" "blkuc4" "1280,881.5" "1" "1" "0")
(command "_insert" "blkuc4" "1280,881.13" "1" "1" "180")
(command "_insert" "blkuc4" "1280,881.87" "1" "1" "0")
(command "_insert" "blkuc4" "1280,881.5" "1" "1" "180")
(command "_insert" "blkuc4" "1280,882.24" "1" "1" "0")
(command "_insert" "blkuc4" "1280,881.87" "1" "1" "180")
(command "_insert" "blkuc4" "1280,882.61" "1" "1" "0")
(command "_insert" "blkuc4" "1280,882.24" "1" "1" "180")
(command "_insert" "blkuc4" "1280,882.98" "1" "1" "0")
(command "_insert" "blkuc4" "1280,882.61" "1" "1" "180")
(command "_insert" "blkuc4" "1280,883.35" "1" "1" "0")
(command "_insert" "blkuc4" "1280,882.98" "1" "1" "180")
(command "_insert" "blkuc4" "1280,883.72" "1" "1" "0")
(command "_insert" "blkuc4" "1280,883.35" "1" "1" "180")
(command "_insert" "blkuc4" "1280,884.09" "1" "1" "0")
(command "_insert" "blkuc4" "1280,883.72" "1" "1" "180")
(command "_insert" "blkuc4" "1280,884.46" "1" "1" "0")
(command "_insert" "blkuc4" "1280,884.09" "1" "1" "180")
(command "_insert" "blkuc4" "1280,884.83" "1" "1" "0")
(command "_insert" "blkuc4" "1280,884.46" "1" "1" "180")
(command "_insert" "blkuc4" "1280,885.2" "1" "1" "0")
(command "_insert" "blkuc4" "1280,884.83" "1" "1" "180")
(command "_insert" "blkuc4" "1280,885.57" "1" "1" "0")
(command "_insert" "blkuc4" "1280,885.2" "1" "1" "180")
(command "_insert" "blkuc4" "1280,885.94" "1" "1" "0")
(command "_insert" "blkuc4" "1280,885.57" "1" "1" "180")
(command "_insert" "blkuc4" "1280,886.31" "1" "1" "0")
(command "_insert" "blkuc4" "1280,885.94" "1" "1" "180")
(command "_insert" "blkuc4" "1280,886.68" "1" "1" "0")
(command "_insert" "blkuc4" "1280,886.31" "1" "1" "180")
(command "_insert" "blkuc4" "1280,887.05" "1" "1" "0")
(command "_insert" "blkuc4" "1280,886.68" "1" "1" "180")
(command "_insert" "blkuc4" "1280,887.42" "1" "1" "0")
(command "_insert" "blkuc4" "1280,887.05" "1" "1" "180")
(command "_insert" "blkuc4" "1280,887.79" "1" "1" "0")
(command "_insert" "blkuc4" "1280,887.42" "1" "1" "180")
(command "_insert" "blkuc4" "1280,888.16" "1" "1" "0")
(command "_insert" "blkuc4" "1280,887.79" "1" "1" "180")
(command "_insert" "blkuc4" "1280,888.53" "1" "1" "0")
(command "_insert" "blkuc4" "1280,888.16" "1" "1" "180")
(command "_insert" "blkuc4" "1280,888.9" "1" "1" "0")
(command "_insert" "blkuc4" "1280,888.53" "1" "1" "180")
(command "_insert" "blkuc4" "1280,889.27" "1" "1" "0")
(command "_insert" "blkuc4" "1280,888.9" "1" "1" "180")
(command "_insert" "blkuc4" "1280,889.64" "1" "1" "0")
(command "_insert" "blkuc4" "1280,889.27" "1" "1" "180")
(command "_insert" "blkuc4" "1280,890.01" "1" "1" "0")
(command "_insert" "blkuc4" "1280,889.64" "1" "1" "180")
(command "_insert" "blkuc4" "1280,890.38" "1" "1" "0")
(command "_insert" "blkuc4" "1280,890.01" "1" "1" "180")
(command "_insert" "blkuc4" "1280,890.75" "1" "1" "0")
(command "_insert" "blkuc4" "1280,890.38" "1" "1" "180")
(command "_insert" "blkuc4" "1280,891.12" "1" "1" "0")
(command "_insert" "blkuc4" "1280,890.75" "1" "1" "180")
(command "_insert" "blkuc4" "1280,891.49" "1" "1" "0")
(command "_insert" "blkuc4" "1280,891.12" "1" "1" "180")
(command "_insert" "blkuc4" "1280,891.86" "1" "1" "0")
(command "_insert" "blkuc4" "1280,891.49" "1" "1" "180")
(command "_insert" "blkuc4" "1280,892.23" "1" "1" "0")
(command "_insert" "blkuc4" "1280,891.86" "1" "1" "180")
(command "_insert" "blkuc4" "1280,892.6" "1" "1" "0")
(command "_insert" "blkuc4" "1280,892.23" "1" "1" "180")
(command "_insert" "blkuc4" "1280,892.97" "1" "1" "0")
(command "_insert" "blkuc4" "1280,892.6" "1" "1" "180")
(command "_insert" "blkuc4" "1280,893.34" "1" "1" "0")
(command "_insert" "blkuc4" "1280,892.97" "1" "1" "180")
(command "_insert" "blkuc4" "1280,893.71" "1" "1" "0")
(command "_insert" "blkuc4" "1280,893.34" "1" "1" "180")
(command "_insert" "blkuc4" "1280,894.08" "1" "1" "0")
(command "_insert" "blkuc4" "1280,893.71" "1" "1" "180")
(command "_insert" "blkuc4" "1280,894.45" "1" "1" "0")
(command "_insert" "blkuc4" "1280,894.08" "1" "1" "180")
(command "_insert" "blkuc4" "1280,894.82" "1" "1" "0")
(command "_insert" "blkuc4" "1280,894.45" "1" "1" "180")
(command "_insert" "blkuc4" "1280,895.19" "1" "1" "0")
(command "_insert" "blkuc4" "1280,894.82" "1" "1" "180")
(command "_insert" "blkuc4" "1280,895.56" "1" "1" "0")
(command "_insert" "blkuc4" "1280,895.19" "1" "1" "180")
(command "_insert" "blkuc4" "1280,895.93" "1" "1" "0")
(command "_insert" "blkuc4" "1280,895.56" "1" "1" "180")
(command "_insert" "blkuc4" "1280,896.3" "1" "1" "0")
(command "_insert" "blkuc4" "1280,895.93" "1" "1" "180")
(command "_insert" "blkuc4" "1280,896.67" "1" "1" "0")
(command "_insert" "blkuc4" "1280,896.3" "1" "1" "180")
(command "_insert" "blkuc4" "1280,897.04" "1" "1" "0")
(command "_insert" "blkuc4" "1280,896.67" "1" "1" "180")
(command "_insert" "blkuc4" "1280,897.41" "1" "1" "0")
(command "_insert" "blkuc4" "1280,897.04" "1" "1" "180")
(command "_insert" "blkuc4" "1280,897.78" "1" "1" "0")
(command "_insert" "blkuc4" "1280,897.41" "1" "1" "180")
(command "_insert" "blkuc4" "1280,898.15" "1" "1" "0")
(command "_insert" "blkuc4" "1280,897.78" "1" "1" "180")
(command "_insert" "blkuc4" "1280,898.52" "1" "1" "0")
(command "_insert" "blkuc4" "1280,898.15" "1" "1" "180")
(command "_insert" "blkuc4" "1280,898.89" "1" "1" "0")
(command "_insert" "blkuc4" "1280,898.52" "1" "1" "180")
(command "_insert" "blkuc4" "1280,899.26" "1" "1" "0")
(command "_insert" "blkuc4" "1280,898.89" "1" "1" "180")
(command "_insert" "blkuc4" "1280,899.63" "1" "1" "0")
(command "_insert" "blkuc4" "1280,899.26" "1" "1" "180")
(command "_insert" "blkuc4" "1280,900" "1" "1" "0")
(command "_insert" "blkuc4" "1280,899.63" "1" "1" "180")
(command "_insert" "blkuc4" "1280,900.37" "1" "1" "0")
(command "_insert" "blkuc4" "1280,900" "1" "1" "180")
(command "_insert" "blkuc4" "1280,900.74" "1" "1" "0")
(command "_insert" "blkuc4" "1280,900.37" "1" "1" "180")
(command "_insert" "blkuc4" "1280,901.11" "1" "1" "0")
(command "_insert" "blkuc4" "1280,900.74" "1" "1" "180")
(command "_insert" "blkuc4" "1280,901.48" "1" "1" "0")
(command "_insert" "blkuc4" "1280,901.11" "1" "1" "180")
(command "_insert" "blkuc4" "1280,901.85" "1" "1" "0")
(command "_insert" "blkuc4" "1280,901.48" "1" "1" "180")
(command "_insert" "blkuc4" "1280,902.22" "1" "1" "0")
(command "_insert" "blkuc4" "1280,901.85" "1" "1" "180")
(command "_insert" "blkuc4" "1280,902.59" "1" "1" "0")
(command "_insert" "blkuc4" "1280,902.22" "1" "1" "180")
(command "_insert" "blkuc4" "1280,902.96" "1" "1" "0")
(command "_insert" "blkuc4" "1280,902.59" "1" "1" "180")
(command "_insert" "blkuc4" "1280,903.33" "1" "1" "0")
(command "_insert" "blkuc4" "1280,902.96" "1" "1" "180")
(command "_insert" "blkuc4" "1280,903.7" "1" "1" "0")
(command "_insert" "blkuc4" "1280,903.33" "1" "1" "180")
(command "_insert" "blkuc4" "1280,904.07" "1" "1" "0")
(command "_insert" "blkuc4" "1280,903.7" "1" "1" "180")
(command "_insert" "blkuc4" "1280,904.44" "1" "1" "0")
(command "_insert" "blkuc4" "1280,904.07" "1" "1" "180")
(command "_insert" "blkuc4" "1280,904.81" "1" "1" "0")
(command "_insert" "blkuc4" "1280,904.44" "1" "1" "180")
(command "_insert" "blkuc4" "1280,905.18" "1" "1" "0")
(command "_insert" "blkuc4" "1280,904.81" "1" "1" "180")
(command "_insert" "blkuc4" "1280,905.55" "1" "1" "0")
(command "_insert" "blkuc4" "1280,905.18" "1" "1" "180")
(command "_insert" "blkuc4" "1280,905.92" "1" "1" "0")
(command "_insert" "blkuc4" "1280,905.55" "1" "1" "180")
(command "_insert" "blkuc4" "1280,906.29" "1" "1" "0")
(command "_insert" "blkuc4" "1280,905.92" "1" "1" "180")
(command "_insert" "blkuc4" "1280,906.66" "1" "1" "0")
(command "_insert" "blkuc4" "1280,906.29" "1" "1" "180")
(command "_insert" "blkuc4" "1280,907.03" "1" "1" "0")
(command "_insert" "blkuc4" "1280,906.66" "1" "1" "180")
(command "_insert" "blkuc4" "1280,907.4" "1" "1" "0")
(command "_insert" "blkuc4" "1280,907.03" "1" "1" "180")
(command "_insert" "blkuc4" "1280,907.77" "1" "1" "0")
(command "_insert" "blkuc4" "1280,907.4" "1" "1" "180")
(command "_insert" "blkuc4" "1280,908.14" "1" "1" "0")
(command "_insert" "blkuc4" "1280,907.77" "1" "1" "180")
(command "_insert" "blkuc4" "1280,908.51" "1" "1" "0")
(command "_insert" "blkuc4" "1280,908.14" "1" "1" "180")
(command "_insert" "blkuc4" "1280,908.88" "1" "1" "0")
(command "_insert" "blkuc4" "1280,908.51" "1" "1" "180")
(command "_insert" "blkuc4" "1280,909.25" "1" "1" "0")
(command "_insert" "blkuc4" "1280,908.88" "1" "1" "180")
(command "_insert" "blkuc4" "1280,909.62" "1" "1" "0")
(command "_insert" "blkuc4" "1280,909.25" "1" "1" "180")
(command "_insert" "blkuc4" "1280,909.99" "1" "1" "0")
(command "_insert" "blkuc4" "1280,909.62" "1" "1" "180")
(command "_insert" "blkuc4" "1280,910.36" "1" "1" "0")
(command "_insert" "blkuc4" "1280,909.99" "1" "1" "180")
(command "_insert" "blkuc4" "1280,910.73" "1" "1" "0")
(command "_insert" "blkuc4" "1280,910.36" "1" "1" "180")
(command "_insert" "blkuc4" "1280,911.1" "1" "1" "0")
(command "_insert" "blkuc4" "1280,910.73" "1" "1" "180")
(command "_insert" "blkuc4" "1280,911.47" "1" "1" "0")
(command "_insert" "blkuc4" "1280,911.1" "1" "1" "180")
(command "_insert" "blkuc4" "1280,911.84" "1" "1" "0")
(command "_insert" "blkuc4" "1280,911.47" "1" "1" "180")
(command "_insert" "blkuc4" "1280,912.21" "1" "1" "0")
(command "_insert" "blkuc4" "1280,911.84" "1" "1" "180")
(command "_insert" "blkuc4" "1280,912.58" "1" "1" "0")
(command "_insert" "blkuc4" "1280,912.21" "1" "1" "180")
(command "_insert" "blkuc4" "1280,912.95" "1" "1" "0")
(command "_insert" "blkuc4" "1280,912.58" "1" "1" "180")
(command "_insert" "blkuc4" "1280,913.32" "1" "1" "0")
(command "_insert" "blkuc4" "1280,912.95" "1" "1" "180")
(command "_insert" "blkuc4" "1280,913.69" "1" "1" "0")
(command "_insert" "blkuc4" "1280,913.32" "1" "1" "180")
(command "_insert" "blkuc4" "1280,914.06" "1" "1" "0")
(command "_insert" "blkuc4" "1280,913.69" "1" "1" "180")
(command "_insert" "blkuc4" "1280,914.43" "1" "1" "0")
(command "_insert" "blkuc4" "1280,914.06" "1" "1" "180")
(command "_insert" "blkuc4" "1280,914.8" "1" "1" "0")
(command "_insert" "blkuc4" "1280,914.43" "1" "1" "180")
(command "_insert" "blkuc4" "1280,915.17" "1" "1" "0")
(command "_insert" "blkuc4" "1280,914.8" "1" "1" "180")
(command "_insert" "blkuc4" "1280,915.54" "1" "1" "0")
(command "_insert" "blkuc4" "1280,915.17" "1" "1" "180")
(command "_insert" "blkuc4" "1280,915.91" "1" "1" "0")
(command "_insert" "blkuc4" "1280,915.54" "1" "1" "180")
(command "_insert" "blkuc4" "1280,916.28" "1" "1" "0")
(command "_insert" "blkuc4" "1280,915.91" "1" "1" "180")
(command "_insert" "blkuc4" "1280,916.65" "1" "1" "0")
(command "_insert" "blkuc4" "1280,916.28" "1" "1" "180")
(command "_insert" "blkuc4" "1280,917.02" "1" "1" "0")
(command "_insert" "blkuc4" "1280,916.65" "1" "1" "180")
(command "_insert" "blkuc4" "1280,917.39" "1" "1" "0")
(command "_insert" "blkuc4" "1280,917.02" "1" "1" "180")
(command "_insert" "blkuc4" "1280,917.76" "1" "1" "0")
(command "_insert" "blkuc4" "1280,917.39" "1" "1" "180")
(command "_insert" "blkuc4" "1280,918.13" "1" "1" "0")
(command "_insert" "blkuc4" "1280,917.76" "1" "1" "180")
(command "_insert" "blkuc4" "1280,918.5" "1" "1" "0")
(command "_insert" "blkuc4" "1280,918.13" "1" "1" "180")
(command "_insert" "blkuc4" "1280,918.87" "1" "1" "0")
(command "_insert" "blkuc4" "1280,918.5" "1" "1" "180")
(command "_insert" "blkuc4" "1280,919.24" "1" "1" "0")
(command "_insert" "blkuc4" "1280,918.87" "1" "1" "180")
(command "_insert" "blkuc4" "1280,919.61" "1" "1" "0")
(command "_insert" "blkuc4" "1280,919.24" "1" "1" "180")
(command "_insert" "blkuc4" "1280,919.98" "1" "1" "0")
(command "_insert" "blkuc4" "1280,919.61" "1" "1" "180")
(command "_insert" "blkuc4" "1280,920.35" "1" "1" "0")
(command "_insert" "blkuc4" "1280,919.98" "1" "1" "180")
(command "_insert" "blkuc4" "1280,920.72" "1" "1" "0")
(command "_insert" "blkuc4" "1280,920.35" "1" "1" "180")
(command "_insert" "blkuc4" "1280,921.09" "1" "1" "0")
(command "_insert" "blkuc4" "1280,920.72" "1" "1" "180")
(command "_insert" "blkuc4" "1280,921.46" "1" "1" "0")
(command "_insert" "blkuc4" "1280,921.09" "1" "1" "180")
(command "_insert" "blkuc4" "1280,921.83" "1" "1" "0")
(command "_insert" "blkuc4" "1280,921.46" "1" "1" "180")
(command "_insert" "blkuc4" "1280,922.2" "1" "1" "0")
(command "_insert" "blkuc4" "1280,921.83" "1" "1" "180")
(command "_insert" "blkuc4" "1280,922.57" "1" "1" "0")
(command "_insert" "blkuc4" "1280,922.2" "1" "1" "180")
(command "_insert" "blkuc4" "1280,922.94" "1" "1" "0")
(command "_insert" "blkuc4" "1280,922.57" "1" "1" "180")
(command "_insert" "blkuc4" "1280,923.31" "1" "1" "0")
(command "_insert" "blkuc4" "1280,922.94" "1" "1" "180")
(command "_insert" "blkuc4" "1280,923.68" "1" "1" "0")
(command "_insert" "blkuc4" "1280,923.31" "1" "1" "180")
(command "_insert" "blkuc4" "1280,924.05" "1" "1" "0")
(command "_insert" "blkuc4" "1280,923.68" "1" "1" "180")
(command "_insert" "blkuc4" "1280,924.42" "1" "1" "0")
(command "_insert" "blkuc4" "1280,924.05" "1" "1" "180")
(command "_insert" "blkuc4" "1280,924.79" "1" "1" "0")
(command "_insert" "blkuc4" "1280,924.42" "1" "1" "180")
(command "_insert" "blkuc4" "1280,925.16" "1" "1" "0")
(command "_insert" "blkuc4" "1280,924.79" "1" "1" "180")
(command "_insert" "blkuc4" "1280,925.53" "1" "1" "0")
(command "_insert" "blkuc4" "1280,925.16" "1" "1" "180")
(command "_insert" "blkuc4" "1280,925.9" "1" "1" "0")
(command "_insert" "blkuc4" "1280,925.53" "1" "1" "180")
(command "_insert" "blkuc4" "1280,926.27" "1" "1" "0")
(command "_insert" "blkuc4" "1280,925.9" "1" "1" "180")
(command "_insert" "blkuc4" "1280,926.64" "1" "1" "0")
(command "_insert" "blkuc4" "1280,926.27" "1" "1" "180")
(command "_insert" "blkuc4" "1280,927.01" "1" "1" "0")
(command "_insert" "blkuc4" "1280,926.64" "1" "1" "180")
(command "_insert" "blkuc4" "1280,927.38" "1" "1" "0")
(command "_insert" "blkuc4" "1280,927.01" "1" "1" "180")
(command "_insert" "blkuc4" "1280,927.75" "1" "1" "0")
(command "_insert" "blkuc4" "1280,927.38" "1" "1" "180")
(command "_layer" "set" "phccover" "")
(command "_rectangle" "1278.904,933.3" "1281.096,866.7")
(command "_layer" "set" "nitride" "")
(setq phc4 currobj)
(command "_layer" "set" "cover" "")
(command "_rectangle" "1278.904,836.7" "1281.096,963.3")
(command "_layer" "set" "nitride" "")
(command "_layer" "set" "text" "")
(command "_circle" "1277.954,846.7" "0.075")
(command "_circle" "1277.579,846.7" "0.15")
(command "_circle" "1277.204,846.7" "0.075")
(command "_circle" "1276.829,846.7" "0.15")
(command "_circle" "1277.954,848.7" "0.075")
(command "_circle" "1277.579,848.7" "0.075")
(command "_circle" "1277.204,848.7" "0.15")
(command "_circle" "1276.829,848.7" "0.15")
(command "_circle" "1277.954,850.7" "0.075")
(command "_circle" "1277.579,850.7" "0.15")
(command "_circle" "1277.204,850.7" "0.15")
(command "_circle" "1276.829,850.7" "0.15")
(command "_circle" "1277.954,852.7" "0.075")
(command "_circle" "1277.579,852.7" "0.075")
(command "_circle" "1277.204,852.7" "0.075")
(command "_circle" "1276.829,852.7" "0.075")
(command "_circle" "1276.454,852.7" "0.15")
(command "_circle" "1277.954,854.7" "0.075")
(command "_circle" "1277.579,854.7" "0.15")
(command "_circle" "1277.204,854.7" "0.075")
(command "_circle" "1276.829,854.7" "0.075")
(command "_circle" "1276.454,854.7" "0.15")
(command "_circle" "1277.954,856.7" "0.075")
(command "_circle" "1277.579,856.7" "0.075")
(command "_circle" "1277.204,856.7" "0.15")
(command "_circle" "1276.829,856.7" "0.075")
(command "_circle" "1276.454,856.7" "0.15")
(command "_circle" "1277.954,858.7" "0.075")
(command "_circle" "1277.579,858.7" "0.15")
(command "_circle" "1277.204,858.7" "0.15")
(command "_circle" "1276.829,858.7" "0.075")
(command "_circle" "1276.454,858.7" "0.15")
(command "_circle" "1277.954,860.7" "0.075")
(command "_circle" "1277.579,860.7" "0.075")
(command "_circle" "1277.204,860.7" "0.075")
(command "_circle" "1276.829,860.7" "0.15")
(command "_circle" "1276.454,860.7" "0.15")
(command "_circle" "1277.954,862.7" "0.075")
(command "_circle" "1277.579,862.7" "0.15")
(command "_circle" "1277.204,862.7" "0.075")
(command "_circle" "1276.829,862.7" "0.15")
(command "_circle" "1276.454,862.7" "0.15")
(command "_circle" "1277.954,864.7" "0.075")
(command "_circle" "1277.579,864.7" "0.075")
(command "_circle" "1277.204,864.7" "0.15")
(command "_circle" "1276.829,864.7" "0.15")
(command "_circle" "1276.454,864.7" "0.15")
(command "_circle" "1277.954,866.7" "0.075")
(command "_circle" "1277.579,866.7" "0.15")
(command "_circle" "1277.204,866.7" "0.15")
(command "_circle" "1276.829,866.7" "0.15")
(command "_circle" "1276.454,866.7" "0.15")
(command "_circle" "1277.954,868.7" "0.075")
(command "_circle" "1277.579,868.7" "0.075")
(command "_circle" "1277.204,868.7" "0.075")
(command "_circle" "1276.829,868.7" "0.075")
(command "_circle" "1276.454,868.7" "0.075")
(command "_circle" "1276.079,868.7" "0.15")
(command "_circle" "1277.954,870.7" "0.075")
(command "_circle" "1277.579,870.7" "0.15")
(command "_circle" "1277.204,870.7" "0.075")
(command "_circle" "1276.829,870.7" "0.075")
(command "_circle" "1276.454,870.7" "0.075")
(command "_circle" "1276.079,870.7" "0.15")
(command "_circle" "1277.954,872.7" "0.075")
(command "_circle" "1277.579,872.7" "0.075")
(command "_circle" "1277.204,872.7" "0.15")
(command "_circle" "1276.829,872.7" "0.075")
(command "_circle" "1276.454,872.7" "0.075")
(command "_circle" "1276.079,872.7" "0.15")
(command "_circle" "1277.954,874.7" "0.075")
(command "_circle" "1277.579,874.7" "0.15")
(command "_circle" "1277.204,874.7" "0.15")
(command "_circle" "1276.829,874.7" "0.075")
(command "_circle" "1276.454,874.7" "0.075")
(command "_circle" "1276.079,874.7" "0.15")
(command "_circle" "1277.954,876.7" "0.075")
(command "_circle" "1277.579,876.7" "0.075")
(command "_circle" "1277.204,876.7" "0.075")
(command "_circle" "1276.829,876.7" "0.15")
(command "_circle" "1276.454,876.7" "0.075")
(command "_circle" "1276.079,876.7" "0.15")
(command "_circle" "1277.954,878.7" "0.075")
(command "_circle" "1277.579,878.7" "0.15")
(command "_circle" "1277.204,878.7" "0.075")
(command "_circle" "1276.829,878.7" "0.15")
(command "_circle" "1276.454,878.7" "0.075")
(command "_circle" "1276.079,878.7" "0.15")
(command "_circle" "1277.954,880.7" "0.075")
(command "_circle" "1277.579,880.7" "0.075")
(command "_circle" "1277.204,880.7" "0.15")
(command "_circle" "1276.829,880.7" "0.15")
(command "_circle" "1276.454,880.7" "0.075")
(command "_circle" "1276.079,880.7" "0.15")
(command "_circle" "1277.954,882.7" "0.075")
(command "_circle" "1277.579,882.7" "0.15")
(command "_circle" "1277.204,882.7" "0.15")
(command "_circle" "1276.829,882.7" "0.15")
(command "_circle" "1276.454,882.7" "0.075")
(command "_circle" "1276.079,882.7" "0.15")
(command "_circle" "1277.954,884.7" "0.075")
(command "_circle" "1277.579,884.7" "0.075")
(command "_circle" "1277.204,884.7" "0.075")
(command "_circle" "1276.829,884.7" "0.075")
(command "_circle" "1276.454,884.7" "0.15")
(command "_circle" "1276.079,884.7" "0.15")
(command "_circle" "1277.954,886.7" "0.075")
(command "_circle" "1277.579,886.7" "0.15")
(command "_circle" "1277.204,886.7" "0.075")
(command "_circle" "1276.829,886.7" "0.075")
(command "_circle" "1276.454,886.7" "0.15")
(command "_circle" "1276.079,886.7" "0.15")
(command "_circle" "1277.954,888.7" "0.075")
(command "_circle" "1277.579,888.7" "0.075")
(command "_circle" "1277.204,888.7" "0.15")
(command "_circle" "1276.829,888.7" "0.075")
(command "_circle" "1276.454,888.7" "0.15")
(command "_circle" "1276.079,888.7" "0.15")
(command "_circle" "1277.954,890.7" "0.075")
(command "_circle" "1277.579,890.7" "0.15")
(command "_circle" "1277.204,890.7" "0.15")
(command "_circle" "1276.829,890.7" "0.075")
(command "_circle" "1276.454,890.7" "0.15")
(command "_circle" "1276.079,890.7" "0.15")
(command "_circle" "1277.954,892.7" "0.075")
(command "_circle" "1277.579,892.7" "0.075")
(command "_circle" "1277.204,892.7" "0.075")
(command "_circle" "1276.829,892.7" "0.15")
(command "_circle" "1276.454,892.7" "0.15")
(command "_circle" "1276.079,892.7" "0.15")
(command "_circle" "1277.954,894.7" "0.075")
(command "_circle" "1277.579,894.7" "0.15")
(command "_circle" "1277.204,894.7" "0.075")
(command "_circle" "1276.829,894.7" "0.15")
(command "_circle" "1276.454,894.7" "0.15")
(command "_circle" "1276.079,894.7" "0.15")
(command "_circle" "1277.954,896.7" "0.075")
(command "_circle" "1277.579,896.7" "0.075")
(command "_circle" "1277.204,896.7" "0.15")
(command "_circle" "1276.829,896.7" "0.15")
(command "_circle" "1276.454,896.7" "0.15")
(command "_circle" "1276.079,896.7" "0.15")
(command "_circle" "1277.954,898.7" "0.075")
(command "_circle" "1277.579,898.7" "0.15")
(command "_circle" "1277.204,898.7" "0.15")
(command "_circle" "1276.829,898.7" "0.15")
(command "_circle" "1276.454,898.7" "0.15")
(command "_circle" "1276.079,898.7" "0.15")
(command "_circle" "1277.954,900.7" "0.075")
(command "_circle" "1277.579,900.7" "0.075")
(command "_circle" "1277.204,900.7" "0.075")
(command "_circle" "1276.829,900.7" "0.075")
(command "_circle" "1276.454,900.7" "0.075")
(command "_circle" "1276.079,900.7" "0.075")
(command "_circle" "1275.704,900.7" "0.15")
(command "_circle" "1277.954,902.7" "0.075")
(command "_circle" "1277.579,902.7" "0.15")
(command "_circle" "1277.204,902.7" "0.075")
(command "_circle" "1276.829,902.7" "0.075")
(command "_circle" "1276.454,902.7" "0.075")
(command "_circle" "1276.079,902.7" "0.075")
(command "_circle" "1275.704,902.7" "0.15")
(command "_circle" "1277.954,904.7" "0.075")
(command "_circle" "1277.579,904.7" "0.075")
(command "_circle" "1277.204,904.7" "0.15")
(command "_circle" "1276.829,904.7" "0.075")
(command "_circle" "1276.454,904.7" "0.075")
(command "_circle" "1276.079,904.7" "0.075")
(command "_circle" "1275.704,904.7" "0.15")
(command "_circle" "1277.954,906.7" "0.075")
(command "_circle" "1277.579,906.7" "0.15")
(command "_circle" "1277.204,906.7" "0.15")
(command "_circle" "1276.829,906.7" "0.075")
(command "_circle" "1276.454,906.7" "0.075")
(command "_circle" "1276.079,906.7" "0.075")
(command "_circle" "1275.704,906.7" "0.15")
(command "_circle" "1277.954,908.7" "0.075")
(command "_circle" "1277.579,908.7" "0.075")
(command "_circle" "1277.204,908.7" "0.075")
(command "_circle" "1276.829,908.7" "0.15")
(command "_circle" "1276.454,908.7" "0.075")
(command "_circle" "1276.079,908.7" "0.075")
(command "_circle" "1275.704,908.7" "0.15")
(command "_circle" "1277.954,910.7" "0.075")
(command "_circle" "1277.579,910.7" "0.15")
(command "_circle" "1277.204,910.7" "0.075")
(command "_circle" "1276.829,910.7" "0.15")
(command "_circle" "1276.454,910.7" "0.075")
(command "_circle" "1276.079,910.7" "0.075")
(command "_circle" "1275.704,910.7" "0.15")
(command "_circle" "1277.954,912.7" "0.075")
(command "_circle" "1277.579,912.7" "0.075")
(command "_circle" "1277.204,912.7" "0.15")
(command "_circle" "1276.829,912.7" "0.15")
(command "_circle" "1276.454,912.7" "0.075")
(command "_circle" "1276.079,912.7" "0.075")
(command "_circle" "1275.704,912.7" "0.15")
(command "_circle" "1277.954,914.7" "0.075")
(command "_circle" "1277.579,914.7" "0.15")
(command "_circle" "1277.204,914.7" "0.15")
(command "_circle" "1276.829,914.7" "0.15")
(command "_circle" "1276.454,914.7" "0.075")
(command "_circle" "1276.079,914.7" "0.075")
(command "_circle" "1275.704,914.7" "0.15")
(command "_circle" "1277.954,916.7" "0.075")
(command "_circle" "1277.579,916.7" "0.075")
(command "_circle" "1277.204,916.7" "0.075")
(command "_circle" "1276.829,916.7" "0.075")
(command "_circle" "1276.454,916.7" "0.15")
(command "_circle" "1276.079,916.7" "0.075")
(command "_circle" "1275.704,916.7" "0.15")
(command "_circle" "1277.954,918.7" "0.075")
(command "_circle" "1277.579,918.7" "0.15")
(command "_circle" "1277.204,918.7" "0.075")
(command "_circle" "1276.829,918.7" "0.075")
(command "_circle" "1276.454,918.7" "0.15")
(command "_circle" "1276.079,918.7" "0.075")
(command "_circle" "1275.704,918.7" "0.15")
(command "_circle" "1277.954,920.7" "0.075")
(command "_circle" "1277.579,920.7" "0.075")
(command "_circle" "1277.204,920.7" "0.15")
(command "_circle" "1276.829,920.7" "0.075")
(command "_circle" "1276.454,920.7" "0.15")
(command "_circle" "1276.079,920.7" "0.075")
(command "_circle" "1275.704,920.7" "0.15")
(command "_circle" "1277.954,922.7" "0.075")
(command "_circle" "1277.579,922.7" "0.15")
(command "_circle" "1277.204,922.7" "0.15")
(command "_circle" "1276.829,922.7" "0.075")
(command "_circle" "1276.454,922.7" "0.15")
(command "_circle" "1276.079,922.7" "0.075")
(command "_circle" "1275.704,922.7" "0.15")
(command "_circle" "1277.954,924.7" "0.075")
(command "_circle" "1277.579,924.7" "0.075")
(command "_circle" "1277.204,924.7" "0.075")
(command "_circle" "1276.829,924.7" "0.15")
(command "_circle" "1276.454,924.7" "0.15")
(command "_circle" "1276.079,924.7" "0.075")
(command "_circle" "1275.704,924.7" "0.15")
(command "_circle" "1277.954,926.7" "0.075")
(command "_circle" "1277.579,926.7" "0.15")
(command "_circle" "1277.204,926.7" "0.075")
(command "_circle" "1276.829,926.7" "0.15")
(command "_circle" "1276.454,926.7" "0.15")
(command "_circle" "1276.079,926.7" "0.075")
(command "_circle" "1275.704,926.7" "0.15")
(command "_circle" "1277.954,928.7" "0.075")
(command "_circle" "1277.579,928.7" "0.075")
(command "_circle" "1277.204,928.7" "0.15")
(command "_circle" "1276.829,928.7" "0.15")
(command "_circle" "1276.454,928.7" "0.15")
(command "_circle" "1276.079,928.7" "0.075")
(command "_circle" "1275.704,928.7" "0.15")
(command "_circle" "1277.954,930.7" "0.075")
(command "_circle" "1277.579,930.7" "0.15")
(command "_circle" "1277.204,930.7" "0.15")
(command "_circle" "1276.829,930.7" "0.15")
(command "_circle" "1276.454,930.7" "0.15")
(command "_circle" "1276.079,930.7" "0.075")
(command "_circle" "1275.704,930.7" "0.15")
(command "_circle" "1277.954,932.7" "0.075")
(command "_circle" "1277.579,932.7" "0.075")
(command "_circle" "1277.204,932.7" "0.075")
(command "_circle" "1276.829,932.7" "0.075")
(command "_circle" "1276.454,932.7" "0.075")
(command "_circle" "1276.079,932.7" "0.15")
(command "_circle" "1275.704,932.7" "0.15")
(command "_circle" "1277.954,934.7" "0.075")
(command "_circle" "1277.579,934.7" "0.15")
(command "_circle" "1277.204,934.7" "0.075")
(command "_circle" "1276.829,934.7" "0.075")
(command "_circle" "1276.454,934.7" "0.075")
(command "_circle" "1276.079,934.7" "0.15")
(command "_circle" "1275.704,934.7" "0.15")
(command "_circle" "1277.954,936.7" "0.075")
(command "_circle" "1277.579,936.7" "0.075")
(command "_circle" "1277.204,936.7" "0.15")
(command "_circle" "1276.829,936.7" "0.075")
(command "_circle" "1276.454,936.7" "0.075")
(command "_circle" "1276.079,936.7" "0.15")
(command "_circle" "1275.704,936.7" "0.15")
(command "_circle" "1277.954,938.7" "0.075")
(command "_circle" "1277.579,938.7" "0.15")
(command "_circle" "1277.204,938.7" "0.15")
(command "_circle" "1276.829,938.7" "0.075")
(command "_circle" "1276.454,938.7" "0.075")
(command "_circle" "1276.079,938.7" "0.15")
(command "_circle" "1275.704,938.7" "0.15")
(command "_circle" "1277.954,940.7" "0.075")
(command "_circle" "1277.579,940.7" "0.075")
(command "_circle" "1277.204,940.7" "0.075")
(command "_circle" "1276.829,940.7" "0.15")
(command "_circle" "1276.454,940.7" "0.075")
(command "_circle" "1276.079,940.7" "0.15")
(command "_circle" "1275.704,940.7" "0.15")
(command "_circle" "1277.954,942.7" "0.075")
(command "_circle" "1277.579,942.7" "0.15")
(command "_circle" "1277.204,942.7" "0.075")
(command "_circle" "1276.829,942.7" "0.15")
(command "_circle" "1276.454,942.7" "0.075")
(command "_circle" "1276.079,942.7" "0.15")
(command "_circle" "1275.704,942.7" "0.15")
(command "_circle" "1277.954,944.7" "0.075")
(command "_circle" "1277.579,944.7" "0.075")
(command "_circle" "1277.204,944.7" "0.15")
(command "_circle" "1276.829,944.7" "0.15")
(command "_circle" "1276.454,944.7" "0.075")
(command "_circle" "1276.079,944.7" "0.15")
(command "_circle" "1275.704,944.7" "0.15")
(command "_circle" "1277.954,946.7" "0.075")
(command "_circle" "1277.579,946.7" "0.15")
(command "_circle" "1277.204,946.7" "0.15")
(command "_circle" "1276.829,946.7" "0.15")
(command "_circle" "1276.454,946.7" "0.075")
(command "_circle" "1276.079,946.7" "0.15")
(command "_circle" "1275.704,946.7" "0.15")
(command "_circle" "1277.954,948.7" "0.075")
(command "_circle" "1277.579,948.7" "0.075")
(command "_circle" "1277.204,948.7" "0.075")
(command "_circle" "1276.829,948.7" "0.075")
(command "_circle" "1276.454,948.7" "0.15")
(command "_circle" "1276.079,948.7" "0.15")
(command "_circle" "1275.704,948.7" "0.15")
(command "_circle" "1277.954,950.7" "0.075")
(command "_circle" "1277.579,950.7" "0.15")
(command "_circle" "1277.204,950.7" "0.075")
(command "_circle" "1276.829,950.7" "0.075")
(command "_circle" "1276.454,950.7" "0.15")
(command "_circle" "1276.079,950.7" "0.15")
(command "_circle" "1275.704,950.7" "0.15")
(command "_circle" "1277.954,952.7" "0.075")
(command "_circle" "1277.579,952.7" "0.075")
(command "_circle" "1277.204,952.7" "0.15")
(command "_circle" "1276.829,952.7" "0.075")
(command "_circle" "1276.454,952.7" "0.15")
(command "_circle" "1276.079,952.7" "0.15")
(command "_circle" "1275.704,952.7" "0.15")
(command "_circle" "1277.954,954.7" "0.075")
(command "_circle" "1277.579,954.7" "0.15")
(command "_circle" "1277.204,954.7" "0.15")
(command "_circle" "1276.829,954.7" "0.075")
(command "_circle" "1276.454,954.7" "0.15")
(command "_circle" "1276.079,954.7" "0.15")
(command "_circle" "1275.704,954.7" "0.15")
(command "_circle" "1277.954,956.7" "0.075")
(command "_circle" "1277.579,956.7" "0.075")
(command "_circle" "1277.204,956.7" "0.075")
(command "_circle" "1276.829,956.7" "0.15")
(command "_circle" "1276.454,956.7" "0.15")
(command "_circle" "1276.079,956.7" "0.15")
(command "_circle" "1275.704,956.7" "0.15")
(command "_circle" "1277.954,958.7" "0.075")
(command "_circle" "1277.579,958.7" "0.15")
(command "_circle" "1277.204,958.7" "0.075")
(command "_circle" "1276.829,958.7" "0.15")
(command "_circle" "1276.454,958.7" "0.15")
(command "_circle" "1276.079,958.7" "0.15")
(command "_circle" "1275.704,958.7" "0.15")
(command "_circle" "1277.954,960.7" "0.075")
(command "_circle" "1277.579,960.7" "0.075")
(command "_circle" "1277.204,960.7" "0.15")
(command "_circle" "1276.829,960.7" "0.15")
(command "_circle" "1276.454,960.7" "0.15")
(command "_circle" "1276.079,960.7" "0.15")
(command "_circle" "1275.704,960.7" "0.15")
(command "_circle" "1277.954,962.7" "0.075")
(command "_circle" "1277.579,962.7" "0.15")
(command "_circle" "1277.204,962.7" "0.15")
(command "_circle" "1276.829,962.7" "0.15")
(command "_circle" "1276.454,962.7" "0.15")
(command "_circle" "1276.079,962.7" "0.15")
(command "_circle" "1275.704,962.7" "0.15")
(command "_layer" "set" "nitride" "")
(command "_layer" "set" "text" "")
(command-s "_text" "1266.904,963.3" "2" "-90" "a = 370 nm" )
(sssetfirst nil (ssget "_L"))
(if (not (numberp (vl-string-search "Mac" (getvar "platform")))) (c:txtexp))
(command "_layer" "set" "nitride" "")
(command "_layer" "set" "text" "")
(command-s "_text" "1263.904,963.3" "2" "-90" "gap = 270 nm" )
(sssetfirst nil (ssget "_L"))
(if (not (numberp (vl-string-search "Mac" (getvar "platform")))) (c:txtexp))
(command "_layer" "set" "nitride" "")
(command "_layer" "set" "text" "")
(command-s "_text" "1260.904,963.3" "2" "-90" "amplitude = 137 nm" )
(sssetfirst nil (ssget "_L"))
(if (not (numberp (vl-string-search "Mac" (getvar "platform")))) (c:txtexp))
(command "_layer" "set" "nitride" "")
(command "_layer" "set" "text" "")
(command-s "_text" "1257.904,963.3" "2" "-90" "start width = 280 nm" )
(sssetfirst nil (ssget "_L"))
(if (not (numberp (vl-string-search "Mac" (getvar "platform")))) (c:txtexp))
(command "_layer" "set" "nitride" "")
(command "_layer" "set" "text" "")
(command-s "_text" "1254.904,963.3" "2" "-90" "width = 276 nm" )
(sssetfirst nil (ssget "_L"))
(if (not (numberp (vl-string-search "Mac" (getvar "platform")))) (c:txtexp))
(command "_layer" "set" "nitride" "")
(command "_layer" "set" "text" "")
(command-s "_text" "1251.904,963.3" "2" "-90" "taper: 15" )
(sssetfirst nil (ssget "_L"))
(if (not (numberp (vl-string-search "Mac" (getvar "platform")))) (c:txtexp))
(command "_layer" "set" "nitride" "")
(command "_layer" "set" "text" "")
(command-s "_text" "1248.904,963.3" "2" "-90" "nominal: 150" )
(sssetfirst nil (ssget "_L"))
(if (not (numberp (vl-string-search "Mac" (getvar "platform")))) (c:txtexp))
(command "_layer" "set" "nitride" "")
(command "_layer" "set" "indicators" "")
(setq coords (list 
(list 1200.415 940) 
(list 1200.415 920) 
(list 1180.415 900) 
(list 1200.415 880) 
(list 1200.415 860) 
(list 1200.415 900) 
(list 1200.415 887.0711) 
(list 1187.4861 900) 
(list 1200.415 912.9289) 
(list 1200.415 900)))
(apply 'command (append '("pline") coords '("c")))
(command "._fillet" "radius" "1" "._fillet" "P" (entlast))
(setq coords (list 
(list 1359.585 940) 
(list 1359.585 920) 
(list 1379.585 900) 
(list 1359.585 880) 
(list 1359.585 860) 
(list 1359.585 900) 
(list 1359.585 887.0711) 
(list 1372.5139 900) 
(list 1359.585 912.9289) 
(list 1359.585 900)))
(apply 'command (append '("pline") coords '("c")))
(command "._fillet" "radius" "1" "._fillet" "P" (entlast))
(command "_layer" "set" "holes" "")
(command "_circle" "1198.0629,914.1124" "0.5")
(command "_circle" "1195.7109,911.7603" "0.5")
(command "_circle" "1193.3588,909.4083" "0.5")
(command "_circle" "1191.0067,907.0562" "0.5")
(command "_circle" "1188.6547,904.7041" "0.5")
(command "_circle" "1186.3026,902.3521" "0.5")
(command "_circle" "1183.9505,900" "0.5")
(command "_circle" "1186.3026,897.6479" "0.5")
(command "_circle" "1188.6547,895.2959" "0.5")
(command "_circle" "1191.0067,892.9438" "0.5")
(command "_circle" "1193.3588,890.5917" "0.5")
(command "_circle" "1195.7109,888.2397" "0.5")
(command "_circle" "1198.0629,885.8876" "0.5")
(command "_circle" "1361.9371,914.1124" "0.5")
(command "_circle" "1364.2891,911.7603" "0.5")
(command "_circle" "1366.6412,909.4083" "0.5")
(command "_circle" "1368.9933,907.0562" "0.5")
(command "_circle" "1371.3453,904.7041" "0.5")
(command "_circle" "1373.6974,902.3521" "0.5")
(command "_circle" "1376.0495,900" "0.5")
(command "_circle" "1373.6974,897.6479" "0.5")
(command "_circle" "1371.3453,895.2959" "0.5")
(command "_circle" "1368.9933,892.9438" "0.5")
(command "_circle" "1366.6412,890.5917" "0.5")
(command "_circle" "1364.2891,888.2397" "0.5")
(command "_circle" "1361.9371,885.8876" "0.5")
(command "_layer" "set" "nitride" "")
(command "_block" "blkcoupler4" "1280,900" coupler4 "")
(command "_insert" "blkcoupler4" "1280,900" "1" "1" "0")
(command "_insert" "blkcoupler4" "1280,900" "1" "1" "180")
(command "_block" "blksinglenanobeam4" "1280,900" singlenanobeam4 "")
(command "_insert" "blksinglenanobeam4" "1280,900" "1" "1" "0")
(command "_insert" "blksinglenanobeam4" "1280,900" "1" "1" "180")
(command "_block" "blkanglednodearray4" "1280,900" anglednodearray4 "")
(command "_insert" "blkanglednodearray4" "1280,900" "1" "1" "0")
(command "_insert" "blkanglednodearray4" "1280,900" "1" "1" "180")
(command "_block" "blkcooledsinglenanobeam4" "1280,900" cooledsinglenanobeam4 "")
(command "_insert" "blkcooledsinglenanobeam4" "1280,900" "1" "1" "0")
(command "_insert" "blkcooledsinglenanobeam4" "1280,900" "1" "1" "180")
(command "_block" "blkyjunction4" "1280,900" yjunction4 "")
(command "_insert" "blkyjunction4" "1280,900" "1" "1" "0")
(command "_insert" "blkyjunction4" "1280,900" "1" "1" "180")
; DRAWING BULGING VEE GROOVE
(command "_layer" "set" "vgroove" "")
(setq coords (list 
(list 1205.415 -605) 
(list 1205.415 0) 
(list 1205.415 0) 
(list 1205.415 1800) 
(list 1205.415 1800) 
(list 1205.415 2405) 
(list 1354.585 2405) 
(list 1354.585 1800) 
(list 1354.585 1800) 
(list 1354.585 0) 
(list 1354.585 0) 
(list 1354.585 -605)))
(apply 'command (append '("pline") coords '("c")))
(command "._fillet" "radius" "0" "._fillet" "P" (entlast))
(command "_layer" "set" "window" "")
(command "_rectangle" "1205.415,-1935" "1354.585,-600")
(command "_rectangle" "1205.415,2400" "1354.585,5300")
(command "_layer" "set" "grid" "")
(command "_rectangle" "1206.415,-1934" "1229.9433,-1909.2133")
(command "_array" "last" "" "R" "75" "3" "25.7867" "24.5283")
(command "_rectangle" "1281,-1934" "1304.5283,-1909.2133")
(command "_array" "last" "" "R" "75" "3" "25.7867" "24.5283")
(command "_rectangle" "1206.415,1" "1229.9433,25.7")
(command "_array" "last" "" "R" "70" "3" "25.7" "24.5283")
(command "_rectangle" "1281,1" "1304.5283,25.7")
(command "_array" "last" "" "R" "70" "3" "25.7" "24.5283")
(command "_rectangle" "1206.415,1801" "1229.9433,1825.9185")
(command "_array" "last" "" "R" "135" "3" "25.9185" "24.5283")
(command "_rectangle" "1281,1801" "1304.5283,1825.9185")
(command "_array" "last" "" "R" "135" "3" "25.9185" "24.5283")
(command "_layer" "set" "vgrooveFDA" "")
(command "_rectangle" "1354.585,-2233" "1205.415,-1933")
(command "_layer" "set" "nitride" "")
(command "_layer" "set" "holes" "")
(command "_circle" "1357.085,331.5" "0.5")
(command "_array" "last" "" "R" "379" "1" "3" "2.5")
(command "_circle" "1202.915,331.5" "0.5")
(command "_array" "last" "" "R" "379" "1" "3" "-2.5")
(command "_layer" "set" "nitride" "")
(command "_layer" "set" "window" "")
(command "_layer" "set" "window" "")
(command "_rectangle" "1359.585,0" "1520.415,1800")
(command "._fillet" "radius" "20" "._fillet" "P" (entlast))
(command "_layer" "set" "grid" "")
(command "_rectangle" "1360.585,1" "1382.4179,25.7")
(command "_array" "last" "" "R" "70" "7" "25.7" "22.8329")
(command "_layer" "set" "nitride" "")
; DRAWING REGION LAYER
(command "_layer" "set" "regionLayer4" "")
(command "_rectangle" "1200,-460" "1360,2260")
(command "_layer" "set" "nitride" "")
(setq coupler4 nil)
(setq singlenanobeam4 nil)
(setq anglednodearray4 nil)
(setq cooledsinglenanobeam4 nil)
(setq yjunction4 nil)
; DEVICE #5
(command "_layer" "set" "window" "")
(command "_circle" "1512.915,-415" "5")
(command "_circle" "1512.915,-402.5" "5")
(command "_circle" "1512.915,-390" "5")
(command "_circle" "1512.915,-377.5" "5")
(command "_circle" "1500.415,-415" "5")
(command "_layer" "set" "nitride" "")
(setq currobj nil)
(setq currobj (ssadd))
; DRAWING COUPLER
(setq coords (list 
(list 1600.0615 -415) 
(list 1600.0615 -413) 
(list 1673.585 -413) 
(list 1673.585 -413) 
(list 1673.9677 -413.0761) 
(list 1674.2921 -413.2929) 
(list 1674.5089 -413.6173) 
(list 1674.585 -414) 
(list 1674.585 -411.8) 
(list 1674.585 -411.8) 
(list 1674.5089 -412.1827) 
(list 1674.2921 -412.5071) 
(list 1673.9677 -412.7239) 
(list 1673.585 -412.8) 
(list 1600.0615 -412.8) 
(list 1600.0615 -410.8) 
(list 1599.9385 -410.8) 
(list 1599.9385 -412.8) 
(list 1526.415 -412.8) 
(list 1526.0323 -412.7239) 
(list 1525.7079 -412.5071) 
(list 1525.4911 -412.1827) 
(list 1525.415 -411.8) 
(list 1525.415 -411.8) 
(list 1525.415 -414) 
(list 1525.4911 -413.6173) 
(list 1525.7079 -413.2929) 
(list 1526.0323 -413.0761) 
(list 1526.415 -413) 
(list 1526.415 -413) 
(list 1599.9385 -413) 
(list 1599.9385 -415)))
(apply 'command (append '("pline") coords '("c")))
(setq currobj (ssadd (entlast) currobj))
(command "._fillet" "radius" "0.3" "._fillet" "P" (entlast))
(command "_layer" "set" "holes" "")
(command "_circle" "1600,-412.9" "0.113")
(setq currobj (ssadd (entlast) currobj))
(command "_layer" "set" "nitride" "")
(command "_layer" "set" "text" "")
(command "_circle" "1599.2,-415" "0.075")
(command "_circle" "1599.2,-414.7" "0.075")
(command "_circle" "1599.2,-414.4" "0.075")
(command "_circle" "1598.9,-415" "0.075")
(command "_circle" "1598.9,-414.7" "0.075")
(command "_circle" "1598.9,-414.4" "0.075")
(command "_circle" "1598.6,-415" "0.075")
(command "_circle" "1598.6,-414.7" "0.075")
(command "_circle" "1598.6,-414.4" "0.075")
(command "_layer" "set" "nitride" "")
(command "_layer" "set" "prebias" "")
(command "_rectangle" "1525.415,-414" "1674.585,-411.8")
(setq currobj (ssadd (entlast) currobj))
(command "_rectangle" "1599.9385,-415" "1600.0615,-410.8")
(setq currobj (ssadd (entlast) currobj))
(command "_layer" "set" "nitride" "")
(setq coupler5 currobj)
(setq currobj nil)
(setq currobj (ssadd))
; DRAWING SINGLE NANOBEAM
(setq coords (list 
(list 1600.0615 -410.8) 
(list 1600.0615 -409.1417) 
(list 1600.0615 -407.4833) 
(list 1600.0615 -405.825) 
(list 1600.0615 -404.1667) 
(list 1600.0615 -402.5083) 
(list 1600.0615 -400.85) 
(list 1600.0615 -399.1917) 
(list 1600.0615 -397.5333) 
(list 1600.0616 -395.875) 
(list 1600.0616 -394.2167) 
(list 1600.0616 -392.5583) 
(list 1600.0616 -390.9) 
(list 1600.0617 -389.2417) 
(list 1600.0617 -387.5833) 
(list 1600.0617 -385.925) 
(list 1600.0618 -384.2667) 
(list 1600.0619 -382.6083) 
(list 1600.0619 -380.95) 
(list 1600.062 -379.2917) 
(list 1600.0621 -377.6333) 
(list 1600.0622 -375.975) 
(list 1600.0623 -374.3167) 
(list 1600.0624 -372.6583) 
(list 1600.0625 -371) 
(list 1600.0626 -369.3417) 
(list 1600.0628 -367.6833) 
(list 1600.0629 -366.025) 
(list 1600.0631 -364.3667) 
(list 1600.0632 -362.7083) 
(list 1600.0634 -361.05) 
(list 1600.0636 -359.3917) 
(list 1600.0638 -357.7333) 
(list 1600.0641 -356.075) 
(list 1600.0643 -354.4167) 
(list 1600.0646 -352.7583) 
(list 1600.0648 -351.1) 
(list 1600.0651 -349.4417) 
(list 1600.0654 -347.7833) 
(list 1600.0657 -346.125) 
(list 1600.0661 -344.4667) 
(list 1600.0664 -342.8083) 
(list 1600.0668 -341.15) 
(list 1600.0672 -339.4917) 
(list 1600.0676 -337.8333) 
(list 1600.068 -336.175) 
(list 1600.0685 -334.5167) 
(list 1600.0689 -332.8583) 
(list 1600.0694 -331.2) 
(list 1600.0699 -329.5417) 
(list 1600.0704 -327.8833) 
(list 1600.071 -326.225) 
(list 1600.0715 -324.5667) 
(list 1600.0721 -322.9083) 
(list 1600.0728 -321.25) 
(list 1600.0734 -319.5917) 
(list 1600.0741 -317.9333) 
(list 1600.0747 -316.275) 
(list 1600.0754 -314.6167) 
(list 1600.0762 -312.9583) 
(list 1600.0769 -311.3) 
(list 1600.0777 -309.6417) 
(list 1600.0785 -307.9833) 
(list 1600.0794 -306.325) 
(list 1600.0802 -304.6667) 
(list 1600.0811 -303.0083) 
(list 1600.082 -301.35) 
(list 1600.083 -299.6917) 
(list 1600.084 -298.0333) 
(list 1600.085 -296.375) 
(list 1600.086 -294.7167) 
(list 1600.0871 -293.0583) 
(list 1600.0882 -291.4) 
(list 1600.0893 -289.7417) 
(list 1600.0905 -288.0833) 
(list 1600.0917 -286.425) 
(list 1600.0929 -284.7667) 
(list 1600.0941 -283.1083) 
(list 1600.0954 -281.45) 
(list 1600.0967 -279.7917) 
(list 1600.0981 -278.1333) 
(list 1600.0995 -276.475) 
(list 1600.1009 -274.8167) 
(list 1600.1024 -273.1583) 
(list 1600.1039 -271.5) 
(list 1600.1054 -269.8417) 
(list 1600.107 -268.1833) 
(list 1600.1086 -266.525) 
(list 1600.1102 -264.8667) 
(list 1600.1119 -263.2083) 
(list 1600.1136 -261.55) 
(list 1600.1154 -259.8917) 
(list 1600.1172 -258.2333) 
(list 1600.119 -256.575) 
(list 1600.1209 -254.9167) 
(list 1600.1228 -253.2583) 
(list 1600.1247 -251.6) 
(list 1600.1267 -249.9417) 
(list 1600.1288 -248.2833) 
(list 1600.1308 -246.625) 
(list 1600.133 -244.9667) 
(list 1600.1351 -243.3083) 
(list 1600.1373 -241.65) 
(list 1600.1396 -239.9917) 
(list 1600.1419 -238.3333) 
(list 1600.1442 -236.675) 
(list 1600.1466 -235.0167) 
(list 1600.1491 -233.3583) 
(list 1600.1515 -231.7) 
(list 1600.1541 -230.0417) 
(list 1600.1566 -228.3833) 
(list 1600.1592 -226.725) 
(list 1600.1619 -225.0667) 
(list 1600.1646 -223.4083) 
(list 1600.1674 -221.75) 
(list 1600.1702 -220.0917) 
(list 1600.1731 -218.4333) 
(list 1600.176 -216.775) 
(list 1600.1789 -215.1167) 
(list 1600.1819 -213.4583) 
(list 1600.185 -211.8) 
(list 1599.815 -211.8) 
(list 1599.8181 -213.4583) 
(list 1599.8211 -215.1167) 
(list 1599.824 -216.775) 
(list 1599.8269 -218.4333) 
(list 1599.8298 -220.0917) 
(list 1599.8326 -221.75) 
(list 1599.8354 -223.4083) 
(list 1599.8381 -225.0667) 
(list 1599.8408 -226.725) 
(list 1599.8434 -228.3833) 
(list 1599.8459 -230.0417) 
(list 1599.8485 -231.7) 
(list 1599.8509 -233.3583) 
(list 1599.8534 -235.0167) 
(list 1599.8558 -236.675) 
(list 1599.8581 -238.3333) 
(list 1599.8604 -239.9917) 
(list 1599.8627 -241.65) 
(list 1599.8649 -243.3083) 
(list 1599.867 -244.9667) 
(list 1599.8692 -246.625) 
(list 1599.8712 -248.2833) 
(list 1599.8733 -249.9417) 
(list 1599.8753 -251.6) 
(list 1599.8772 -253.2583) 
(list 1599.8791 -254.9167) 
(list 1599.881 -256.575) 
(list 1599.8828 -258.2333) 
(list 1599.8846 -259.8917) 
(list 1599.8864 -261.55) 
(list 1599.8881 -263.2083) 
(list 1599.8898 -264.8667) 
(list 1599.8914 -266.525) 
(list 1599.893 -268.1833) 
(list 1599.8946 -269.8417) 
(list 1599.8961 -271.5) 
(list 1599.8976 -273.1583) 
(list 1599.8991 -274.8167) 
(list 1599.9005 -276.475) 
(list 1599.9019 -278.1333) 
(list 1599.9033 -279.7917) 
(list 1599.9046 -281.45) 
(list 1599.9059 -283.1083) 
(list 1599.9071 -284.7667) 
(list 1599.9083 -286.425) 
(list 1599.9095 -288.0833) 
(list 1599.9107 -289.7417) 
(list 1599.9118 -291.4) 
(list 1599.9129 -293.0583) 
(list 1599.914 -294.7167) 
(list 1599.915 -296.375) 
(list 1599.916 -298.0333) 
(list 1599.917 -299.6917) 
(list 1599.918 -301.35) 
(list 1599.9189 -303.0083) 
(list 1599.9198 -304.6667) 
(list 1599.9206 -306.325) 
(list 1599.9215 -307.9833) 
(list 1599.9223 -309.6417) 
(list 1599.9231 -311.3) 
(list 1599.9238 -312.9583) 
(list 1599.9246 -314.6167) 
(list 1599.9253 -316.275) 
(list 1599.9259 -317.9333) 
(list 1599.9266 -319.5917) 
(list 1599.9272 -321.25) 
(list 1599.9279 -322.9083) 
(list 1599.9285 -324.5667) 
(list 1599.929 -326.225) 
(list 1599.9296 -327.8833) 
(list 1599.9301 -329.5417) 
(list 1599.9306 -331.2) 
(list 1599.9311 -332.8583) 
(list 1599.9315 -334.5167) 
(list 1599.932 -336.175) 
(list 1599.9324 -337.8333) 
(list 1599.9328 -339.4917) 
(list 1599.9332 -341.15) 
(list 1599.9336 -342.8083) 
(list 1599.9339 -344.4667) 
(list 1599.9343 -346.125) 
(list 1599.9346 -347.7833) 
(list 1599.9349 -349.4417) 
(list 1599.9352 -351.1) 
(list 1599.9354 -352.7583) 
(list 1599.9357 -354.4167) 
(list 1599.9359 -356.075) 
(list 1599.9362 -357.7333) 
(list 1599.9364 -359.3917) 
(list 1599.9366 -361.05) 
(list 1599.9368 -362.7083) 
(list 1599.9369 -364.3667) 
(list 1599.9371 -366.025) 
(list 1599.9372 -367.6833) 
(list 1599.9374 -369.3417) 
(list 1599.9375 -371) 
(list 1599.9376 -372.6583) 
(list 1599.9377 -374.3167) 
(list 1599.9378 -375.975) 
(list 1599.9379 -377.6333) 
(list 1599.938 -379.2917) 
(list 1599.9381 -380.95) 
(list 1599.9381 -382.6083) 
(list 1599.9382 -384.2667) 
(list 1599.9383 -385.925) 
(list 1599.9383 -387.5833) 
(list 1599.9383 -389.2417) 
(list 1599.9384 -390.9) 
(list 1599.9384 -392.5583) 
(list 1599.9384 -394.2167) 
(list 1599.9384 -395.875) 
(list 1599.9385 -397.5333) 
(list 1599.9385 -399.1917) 
(list 1599.9385 -400.85) 
(list 1599.9385 -402.5083) 
(list 1599.9385 -404.1667) 
(list 1599.9385 -405.825) 
(list 1599.9385 -407.4833) 
(list 1599.9385 -409.1417) 
(list 1599.9385 -410.8)))
(apply 'command (append '("pline") coords '("c")))
(setq currobj (ssadd (entlast) currobj))
(command "_layer" "set" "prebias" "")
(command "_rectangle" "1599.815,-410.8" "1600.185,-211.8")
(setq currobj (ssadd (entlast) currobj))
(command "_layer" "set" "nitride" "")
(setq singlenanobeam5 currobj)
(setq currobj nil)
(setq currobj (ssadd))
; DRAWING NODE ARRAY
(setq coords (list 
(list 1600.185 -211.8) 
(list 1600.5625 -201.8) 
(list 1600.5625 -201.8) 
(list 1600.5625 -200.8) 
(list 1674.585 -212.6864) 
(list 1674.585 -207.7434) 
(list 1600.5625 -197.357) 
(list 1600.5625 -196.357) 
(list 1600.5625 -196.357) 
(list 1600.2625 -186.357) 
(list 1599.7375 -186.357) 
(list 1599.4375 -196.357) 
(list 1599.4375 -196.357) 
(list 1599.4375 -197.357) 
(list 1525.415 -207.7434) 
(list 1525.415 -212.6864) 
(list 1599.4375 -200.8) 
(list 1599.4375 -201.8) 
(list 1599.4375 -201.8) 
(list 1599.815 -211.8)))
(apply 'command (append '("pline") coords '("c")))
(setq currobj (ssadd (entlast) currobj))
(command "_layer" "set" "prebias" "")
(setq coords (list 
(list 1599.4375 -212.6864) 
(list 1599.4375 -200.8) 
(list 1525.415 -212.6864) 
(list 1525.415 -207.7434) 
(list 1599.4375 -197.357) 
(list 1599.4375 -186.357) 
(list 1600.5625 -186.357) 
(list 1600.5625 -197.357) 
(list 1674.585 -207.7434) 
(list 1674.585 -212.6864) 
(list 1600.5625 -200.8) 
(list 1600.5625 -212.6864)))
(apply 'command (append '("pline") coords '("c")))
(setq currobj (ssadd (entlast) currobj))
(command "_layer" "set" "nitride" "")
(command "_layer" "set" "fda1" "")
(setq coords (list 
(list 1600.5625 -200.657) 
(list 1674.585 -212.5434) 
(list 1674.585 -212.3664) 
(list 1600.5625 -200.58)))
(apply 'command (append '("pline") coords '("c")))
(setq currobj (ssadd (entlast) currobj))
(setq coords (list 
(list 1600.5625 -200.437) 
(list 1674.585 -212.2234) 
(list 1674.585 -212.0464) 
(list 1600.5625 -200.36)))
(apply 'command (append '("pline") coords '("c")))
(setq currobj (ssadd (entlast) currobj))
(setq coords (list 
(list 1600.5625 -200.217) 
(list 1674.585 -211.9034) 
(list 1674.585 -211.7264) 
(list 1600.5625 -200.14)))
(apply 'command (append '("pline") coords '("c")))
(setq currobj (ssadd (entlast) currobj))
(setq coords (list 
(list 1600.5625 -199.997) 
(list 1674.585 -211.5834) 
(list 1674.585 -211.4064) 
(list 1600.5625 -199.92)))
(apply 'command (append '("pline") coords '("c")))
(setq currobj (ssadd (entlast) currobj))
(setq coords (list 
(list 1600.5625 -199.777) 
(list 1674.585 -211.2634) 
(list 1674.585 -211.0864) 
(list 1600.5625 -199.7)))
(apply 'command (append '("pline") coords '("c")))
(setq currobj (ssadd (entlast) currobj))
(setq coords (list 
(list 1600.5625 -199.557) 
(list 1674.585 -210.9434) 
(list 1674.585 -210.7664) 
(list 1600.5625 -199.48)))
(apply 'command (append '("pline") coords '("c")))
(setq currobj (ssadd (entlast) currobj))
(setq coords (list 
(list 1600.5625 -199.337) 
(list 1674.585 -210.6234) 
(list 1674.585 -210.4464) 
(list 1600.5625 -199.26)))
(apply 'command (append '("pline") coords '("c")))
(setq currobj (ssadd (entlast) currobj))
(setq coords (list 
(list 1600.5625 -199.117) 
(list 1674.585 -210.3034) 
(list 1674.585 -210.1264) 
(list 1600.5625 -199.04)))
(apply 'command (append '("pline") coords '("c")))
(setq currobj (ssadd (entlast) currobj))
(setq coords (list 
(list 1600.5625 -198.897) 
(list 1674.585 -209.9834) 
(list 1674.585 -209.8064) 
(list 1600.5625 -198.82)))
(apply 'command (append '("pline") coords '("c")))
(setq currobj (ssadd (entlast) currobj))
(setq coords (list 
(list 1600.5625 -198.677) 
(list 1674.585 -209.6634) 
(list 1674.585 -209.4864) 
(list 1600.5625 -198.6)))
(apply 'command (append '("pline") coords '("c")))
(setq currobj (ssadd (entlast) currobj))
(setq coords (list 
(list 1600.5625 -198.457) 
(list 1674.585 -209.3434) 
(list 1674.585 -209.1664) 
(list 1600.5625 -198.38)))
(apply 'command (append '("pline") coords '("c")))
(setq currobj (ssadd (entlast) currobj))
(setq coords (list 
(list 1600.5625 -198.237) 
(list 1674.585 -209.0234) 
(list 1674.585 -208.8464) 
(list 1600.5625 -198.16)))
(apply 'command (append '("pline") coords '("c")))
(setq currobj (ssadd (entlast) currobj))
(setq coords (list 
(list 1600.5625 -198.017) 
(list 1674.585 -208.7034) 
(list 1674.585 -208.5264) 
(list 1600.5625 -197.94)))
(apply 'command (append '("pline") coords '("c")))
(setq currobj (ssadd (entlast) currobj))
(setq coords (list 
(list 1600.5625 -197.797) 
(list 1674.585 -208.3834) 
(list 1674.585 -208.2064) 
(list 1600.5625 -197.72)))
(apply 'command (append '("pline") coords '("c")))
(setq currobj (ssadd (entlast) currobj))
(setq coords (list 
(list 1600.5625 -197.577) 
(list 1674.585 -208.0634) 
(list 1674.585 -207.8864) 
(list 1600.5625 -197.5)))
(apply 'command (append '("pline") coords '("c")))
(setq currobj (ssadd (entlast) currobj))
(setq coords (list 
(list 1599.4375 -197.5) 
(list 1525.415 -207.8864) 
(list 1525.415 -208.0634) 
(list 1599.4375 -197.577)))
(apply 'command (append '("pline") coords '("c")))
(setq currobj (ssadd (entlast) currobj))
(setq coords (list 
(list 1599.4375 -197.72) 
(list 1525.415 -208.2064) 
(list 1525.415 -208.3834) 
(list 1599.4375 -197.797)))
(apply 'command (append '("pline") coords '("c")))
(setq currobj (ssadd (entlast) currobj))
(setq coords (list 
(list 1599.4375 -197.94) 
(list 1525.415 -208.5264) 
(list 1525.415 -208.7034) 
(list 1599.4375 -198.017)))
(apply 'command (append '("pline") coords '("c")))
(setq currobj (ssadd (entlast) currobj))
(setq coords (list 
(list 1599.4375 -198.16) 
(list 1525.415 -208.8464) 
(list 1525.415 -209.0234) 
(list 1599.4375 -198.237)))
(apply 'command (append '("pline") coords '("c")))
(setq currobj (ssadd (entlast) currobj))
(setq coords (list 
(list 1599.4375 -198.38) 
(list 1525.415 -209.1664) 
(list 1525.415 -209.3434) 
(list 1599.4375 -198.457)))
(apply 'command (append '("pline") coords '("c")))
(setq currobj (ssadd (entlast) currobj))
(setq coords (list 
(list 1599.4375 -198.6) 
(list 1525.415 -209.4864) 
(list 1525.415 -209.6634) 
(list 1599.4375 -198.677)))
(apply 'command (append '("pline") coords '("c")))
(setq currobj (ssadd (entlast) currobj))
(setq coords (list 
(list 1599.4375 -198.82) 
(list 1525.415 -209.8064) 
(list 1525.415 -209.9834) 
(list 1599.4375 -198.897)))
(apply 'command (append '("pline") coords '("c")))
(setq currobj (ssadd (entlast) currobj))
(setq coords (list 
(list 1599.4375 -199.04) 
(list 1525.415 -210.1264) 
(list 1525.415 -210.3034) 
(list 1599.4375 -199.117)))
(apply 'command (append '("pline") coords '("c")))
(setq currobj (ssadd (entlast) currobj))
(setq coords (list 
(list 1599.4375 -199.26) 
(list 1525.415 -210.4464) 
(list 1525.415 -210.6234) 
(list 1599.4375 -199.337)))
(apply 'command (append '("pline") coords '("c")))
(setq currobj (ssadd (entlast) currobj))
(setq coords (list 
(list 1599.4375 -199.48) 
(list 1525.415 -210.7664) 
(list 1525.415 -210.9434) 
(list 1599.4375 -199.557)))
(apply 'command (append '("pline") coords '("c")))
(setq currobj (ssadd (entlast) currobj))
(setq coords (list 
(list 1599.4375 -199.7) 
(list 1525.415 -211.0864) 
(list 1525.415 -211.2634) 
(list 1599.4375 -199.777)))
(apply 'command (append '("pline") coords '("c")))
(setq currobj (ssadd (entlast) currobj))
(setq coords (list 
(list 1599.4375 -199.92) 
(list 1525.415 -211.4064) 
(list 1525.415 -211.5834) 
(list 1599.4375 -199.997)))
(apply 'command (append '("pline") coords '("c")))
(setq currobj (ssadd (entlast) currobj))
(setq coords (list 
(list 1599.4375 -200.14) 
(list 1525.415 -211.7264) 
(list 1525.415 -211.9034) 
(list 1599.4375 -200.217)))
(apply 'command (append '("pline") coords '("c")))
(setq currobj (ssadd (entlast) currobj))
(setq coords (list 
(list 1599.4375 -200.36) 
(list 1525.415 -212.0464) 
(list 1525.415 -212.2234) 
(list 1599.4375 -200.437)))
(apply 'command (append '("pline") coords '("c")))
(setq currobj (ssadd (entlast) currobj))
(setq coords (list 
(list 1599.4375 -200.58) 
(list 1525.415 -212.3664) 
(list 1525.415 -212.5434) 
(list 1599.4375 -200.657)))
(apply 'command (append '("pline") coords '("c")))
(setq currobj (ssadd (entlast) currobj))
(command "_layer" "set" "nitride" "")
(command "_layer" "set" "text" "")
(command "_circle" "1598.985,-211.8" "0.075")
(command "_circle" "1598.985,-211.5" "0.075")
(command "_circle" "1598.985,-211.2" "0.075")
(command "_circle" "1598.985,-210.9" "0.075")
(command "_circle" "1598.985,-210.6" "0.075")
(command "_circle" "1598.685,-211.8" "0.075")
(command "_circle" "1598.685,-211.5" "0.075")
(command "_circle" "1598.685,-211.2" "0.075")
(command "_circle" "1598.685,-210.9" "0.075")
(command "_circle" "1598.685,-210.6" "0.075")
(command "_circle" "1598.385,-211.8" "0.075")
(command "_circle" "1598.385,-211.5" "0.075")
(command "_circle" "1598.385,-211.2" "0.075")
(command "_circle" "1598.385,-210.9" "0.075")
(command "_circle" "1598.385,-210.6" "0.075")
(command "_circle" "1598.085,-211.8" "0.075")
(command "_circle" "1598.085,-211.5" "0.075")
(command "_circle" "1598.085,-211.2" "0.075")
(command "_circle" "1598.085,-210.9" "0.075")
(command "_circle" "1598.085,-210.6" "0.075")
(command "_circle" "1597.785,-211.8" "0.075")
(command "_circle" "1597.785,-211.5" "0.075")
(command "_circle" "1597.785,-211.2" "0.075")
(command "_circle" "1597.785,-210.9" "0.075")
(command "_circle" "1597.785,-210.6" "0.075")
(command "_layer" "set" "nitride" "")
(setq anglednodearray5 currobj)
(setq currobj nil)
(setq currobj (ssadd))
; DRAWING COOLED SINGLE NANOBEAM
(setq coords (list 
(list 1600.2625 -186.357) 
(list 1600.2625 -181.357) 
(list 1599.7375 -181.357) 
(list 1599.7375 -186.357)))
(apply 'command (append '("pline") coords '("c")))
(setq currobj (ssadd (entlast) currobj))
(command "_layer" "set" "prebias" "")
(command "_rectangle" "1599.7375,-186.357" "1600.2625,-181.357")
(setq currobj (ssadd (entlast) currobj))
(command "_layer" "set" "nitride" "")
(setq coords (list 
(list 1600.2625 -181.357) 
(list 1600.5625 -171.357) 
(list 1600.5625 -171.357) 
(list 1600.5625 -170.357) 
(list 1674.585 -171.107) 
(list 1674.585 -166.164) 
(list 1600.5625 -166.914) 
(list 1600.5625 -165.914) 
(list 1600.5625 -165.914) 
(list 1600.2625 -155.914) 
(list 1599.7375 -155.914) 
(list 1599.4375 -165.914) 
(list 1599.4375 -165.914) 
(list 1599.4375 -166.914) 
(list 1525.415 -166.164) 
(list 1525.415 -171.107) 
(list 1599.4375 -170.357) 
(list 1599.4375 -171.357) 
(list 1599.4375 -171.357) 
(list 1599.7375 -181.357)))
(apply 'command (append '("pline") coords '("c")))
(setq currobj (ssadd (entlast) currobj))
(command "_layer" "set" "prebias" "")
(setq coords (list 
(list 1599.4375 -181.357) 
(list 1599.4375 -170.357) 
(list 1525.415 -171.107) 
(list 1525.415 -166.164) 
(list 1599.4375 -166.914) 
(list 1599.4375 -155.914) 
(list 1600.5625 -155.914) 
(list 1600.5625 -166.914) 
(list 1674.585 -166.164) 
(list 1674.585 -171.107) 
(list 1600.5625 -170.357) 
(list 1600.5625 -181.357)))
(apply 'command (append '("pline") coords '("c")))
(setq currobj (ssadd (entlast) currobj))
(command "_layer" "set" "nitride" "")
(command "_layer" "set" "fda1" "")
(setq coords (list 
(list 1600.5625 -170.214) 
(list 1674.585 -170.964) 
(list 1674.585 -170.787) 
(list 1600.5625 -170.137)))
(apply 'command (append '("pline") coords '("c")))
(setq currobj (ssadd (entlast) currobj))
(setq coords (list 
(list 1600.5625 -169.994) 
(list 1674.585 -170.644) 
(list 1674.585 -170.467) 
(list 1600.5625 -169.917)))
(apply 'command (append '("pline") coords '("c")))
(setq currobj (ssadd (entlast) currobj))
(setq coords (list 
(list 1600.5625 -169.774) 
(list 1674.585 -170.324) 
(list 1674.585 -170.147) 
(list 1600.5625 -169.697)))
(apply 'command (append '("pline") coords '("c")))
(setq currobj (ssadd (entlast) currobj))
(setq coords (list 
(list 1600.5625 -169.554) 
(list 1674.585 -170.004) 
(list 1674.585 -169.827) 
(list 1600.5625 -169.477)))
(apply 'command (append '("pline") coords '("c")))
(setq currobj (ssadd (entlast) currobj))
(setq coords (list 
(list 1600.5625 -169.334) 
(list 1674.585 -169.684) 
(list 1674.585 -169.507) 
(list 1600.5625 -169.257)))
(apply 'command (append '("pline") coords '("c")))
(setq currobj (ssadd (entlast) currobj))
(setq coords (list 
(list 1600.5625 -169.114) 
(list 1674.585 -169.364) 
(list 1674.585 -169.187) 
(list 1600.5625 -169.037)))
(apply 'command (append '("pline") coords '("c")))
(setq currobj (ssadd (entlast) currobj))
(setq coords (list 
(list 1600.5625 -168.894) 
(list 1674.585 -169.044) 
(list 1674.585 -168.867) 
(list 1600.5625 -168.817)))
(apply 'command (append '("pline") coords '("c")))
(setq currobj (ssadd (entlast) currobj))
(setq coords (list 
(list 1600.5625 -168.674) 
(list 1674.585 -168.724) 
(list 1674.585 -168.547) 
(list 1600.5625 -168.597)))
(apply 'command (append '("pline") coords '("c")))
(setq currobj (ssadd (entlast) currobj))
(setq coords (list 
(list 1600.5625 -168.454) 
(list 1674.585 -168.404) 
(list 1674.585 -168.227) 
(list 1600.5625 -168.377)))
(apply 'command (append '("pline") coords '("c")))
(setq currobj (ssadd (entlast) currobj))
(setq coords (list 
(list 1600.5625 -168.234) 
(list 1674.585 -168.084) 
(list 1674.585 -167.907) 
(list 1600.5625 -168.157)))
(apply 'command (append '("pline") coords '("c")))
(setq currobj (ssadd (entlast) currobj))
(setq coords (list 
(list 1600.5625 -168.014) 
(list 1674.585 -167.764) 
(list 1674.585 -167.587) 
(list 1600.5625 -167.937)))
(apply 'command (append '("pline") coords '("c")))
(setq currobj (ssadd (entlast) currobj))
(setq coords (list 
(list 1600.5625 -167.794) 
(list 1674.585 -167.444) 
(list 1674.585 -167.267) 
(list 1600.5625 -167.717)))
(apply 'command (append '("pline") coords '("c")))
(setq currobj (ssadd (entlast) currobj))
(setq coords (list 
(list 1600.5625 -167.574) 
(list 1674.585 -167.124) 
(list 1674.585 -166.947) 
(list 1600.5625 -167.497)))
(apply 'command (append '("pline") coords '("c")))
(setq currobj (ssadd (entlast) currobj))
(setq coords (list 
(list 1600.5625 -167.354) 
(list 1674.585 -166.804) 
(list 1674.585 -166.627) 
(list 1600.5625 -167.277)))
(apply 'command (append '("pline") coords '("c")))
(setq currobj (ssadd (entlast) currobj))
(setq coords (list 
(list 1600.5625 -167.134) 
(list 1674.585 -166.484) 
(list 1674.585 -166.307) 
(list 1600.5625 -167.057)))
(apply 'command (append '("pline") coords '("c")))
(setq currobj (ssadd (entlast) currobj))
(setq coords (list 
(list 1599.4375 -167.057) 
(list 1525.415 -166.307) 
(list 1525.415 -166.484) 
(list 1599.4375 -167.134)))
(apply 'command (append '("pline") coords '("c")))
(setq currobj (ssadd (entlast) currobj))
(setq coords (list 
(list 1599.4375 -167.277) 
(list 1525.415 -166.627) 
(list 1525.415 -166.804) 
(list 1599.4375 -167.354)))
(apply 'command (append '("pline") coords '("c")))
(setq currobj (ssadd (entlast) currobj))
(setq coords (list 
(list 1599.4375 -167.497) 
(list 1525.415 -166.947) 
(list 1525.415 -167.124) 
(list 1599.4375 -167.574)))
(apply 'command (append '("pline") coords '("c")))
(setq currobj (ssadd (entlast) currobj))
(setq coords (list 
(list 1599.4375 -167.717) 
(list 1525.415 -167.267) 
(list 1525.415 -167.444) 
(list 1599.4375 -167.794)))
(apply 'command (append '("pline") coords '("c")))
(setq currobj (ssadd (entlast) currobj))
(setq coords (list 
(list 1599.4375 -167.937) 
(list 1525.415 -167.587) 
(list 1525.415 -167.764) 
(list 1599.4375 -168.014)))
(apply 'command (append '("pline") coords '("c")))
(setq currobj (ssadd (entlast) currobj))
(setq coords (list 
(list 1599.4375 -168.157) 
(list 1525.415 -167.907) 
(list 1525.415 -168.084) 
(list 1599.4375 -168.234)))
(apply 'command (append '("pline") coords '("c")))
(setq currobj (ssadd (entlast) currobj))
(setq coords (list 
(list 1599.4375 -168.377) 
(list 1525.415 -168.227) 
(list 1525.415 -168.404) 
(list 1599.4375 -168.454)))
(apply 'command (append '("pline") coords '("c")))
(setq currobj (ssadd (entlast) currobj))
(setq coords (list 
(list 1599.4375 -168.597) 
(list 1525.415 -168.547) 
(list 1525.415 -168.724) 
(list 1599.4375 -168.674)))
(apply 'command (append '("pline") coords '("c")))
(setq currobj (ssadd (entlast) currobj))
(setq coords (list 
(list 1599.4375 -168.817) 
(list 1525.415 -168.867) 
(list 1525.415 -169.044) 
(list 1599.4375 -168.894)))
(apply 'command (append '("pline") coords '("c")))
(setq currobj (ssadd (entlast) currobj))
(setq coords (list 
(list 1599.4375 -169.037) 
(list 1525.415 -169.187) 
(list 1525.415 -169.364) 
(list 1599.4375 -169.114)))
(apply 'command (append '("pline") coords '("c")))
(setq currobj (ssadd (entlast) currobj))
(setq coords (list 
(list 1599.4375 -169.257) 
(list 1525.415 -169.507) 
(list 1525.415 -169.684) 
(list 1599.4375 -169.334)))
(apply 'command (append '("pline") coords '("c")))
(setq currobj (ssadd (entlast) currobj))
(setq coords (list 
(list 1599.4375 -169.477) 
(list 1525.415 -169.827) 
(list 1525.415 -170.004) 
(list 1599.4375 -169.554)))
(apply 'command (append '("pline") coords '("c")))
(setq currobj (ssadd (entlast) currobj))
(setq coords (list 
(list 1599.4375 -169.697) 
(list 1525.415 -170.147) 
(list 1525.415 -170.324) 
(list 1599.4375 -169.774)))
(apply 'command (append '("pline") coords '("c")))
(setq currobj (ssadd (entlast) currobj))
(setq coords (list 
(list 1599.4375 -169.917) 
(list 1525.415 -170.467) 
(list 1525.415 -170.644) 
(list 1599.4375 -169.994)))
(apply 'command (append '("pline") coords '("c")))
(setq currobj (ssadd (entlast) currobj))
(setq coords (list 
(list 1599.4375 -170.137) 
(list 1525.415 -170.787) 
(list 1525.415 -170.964) 
(list 1599.4375 -170.214)))
(apply 'command (append '("pline") coords '("c")))
(setq currobj (ssadd (entlast) currobj))
(command "_layer" "set" "nitride" "")
(command "_layer" "set" "text" "")
(command "_circle" "1599.0625,-181.357" "0.075")
(command "_circle" "1599.0625,-181.057" "0.075")
(command "_circle" "1599.0625,-180.757" "0.075")
(command "_circle" "1599.0625,-180.457" "0.075")
(command "_circle" "1599.0625,-180.157" "0.075")
(command "_circle" "1598.7625,-181.357" "0.075")
(command "_circle" "1598.7625,-181.057" "0.075")
(command "_circle" "1598.7625,-180.757" "0.075")
(command "_circle" "1598.7625,-180.457" "0.075")
(command "_circle" "1598.7625,-180.157" "0.075")
(command "_circle" "1598.4625,-181.357" "0.075")
(command "_circle" "1598.4625,-181.057" "0.075")
(command "_circle" "1598.4625,-180.757" "0.075")
(command "_circle" "1598.4625,-180.457" "0.075")
(command "_circle" "1598.4625,-180.157" "0.075")
(command "_circle" "1598.1625,-181.357" "0.075")
(command "_circle" "1598.1625,-181.057" "0.075")
(command "_circle" "1598.1625,-180.757" "0.075")
(command "_circle" "1598.1625,-180.457" "0.075")
(command "_circle" "1598.1625,-180.157" "0.075")
(command "_circle" "1597.8625,-181.357" "0.075")
(command "_circle" "1597.8625,-181.057" "0.075")
(command "_circle" "1597.8625,-180.757" "0.075")
(command "_circle" "1597.8625,-180.457" "0.075")
(command "_circle" "1597.8625,-180.157" "0.075")
(command "_layer" "set" "nitride" "")
(setq coords (list 
(list 1600.2625 -155.914) 
(list 1600.2625 -40.2693) 
(list 1599.7375 -40.2693) 
(list 1599.7375 -155.914)))
(apply 'command (append '("pline") coords '("c")))
(setq currobj (ssadd (entlast) currobj))
(command "_layer" "set" "prebias" "")
(command "_rectangle" "1599.7375,-155.914" "1600.2625,-40.2693")
(setq currobj (ssadd (entlast) currobj))
(command "_layer" "set" "nitride" "")
(setq coords (list 
(list 1600.2625 -40.2693) 
(list 1600.5625 -30.2693) 
(list 1600.5625 -30.2693) 
(list 1600.5625 -29.2693) 
(list 1674.585 -30.0193) 
(list 1674.585 -25.0763) 
(list 1600.5625 -25.8263) 
(list 1600.5625 -24.8263) 
(list 1600.5625 -24.8263) 
(list 1600.2625 -14.8263) 
(list 1599.7375 -14.8263) 
(list 1599.4375 -24.8263) 
(list 1599.4375 -24.8263) 
(list 1599.4375 -25.8263) 
(list 1525.415 -25.0763) 
(list 1525.415 -30.0193) 
(list 1599.4375 -29.2693) 
(list 1599.4375 -30.2693) 
(list 1599.4375 -30.2693) 
(list 1599.7375 -40.2693)))
(apply 'command (append '("pline") coords '("c")))
(setq currobj (ssadd (entlast) currobj))
(command "_layer" "set" "prebias" "")
(setq coords (list 
(list 1599.4375 -40.2693) 
(list 1599.4375 -29.2693) 
(list 1525.415 -30.0193) 
(list 1525.415 -25.0763) 
(list 1599.4375 -25.8263) 
(list 1599.4375 -14.8263) 
(list 1600.5625 -14.8263) 
(list 1600.5625 -25.8263) 
(list 1674.585 -25.0763) 
(list 1674.585 -30.0193) 
(list 1600.5625 -29.2693) 
(list 1600.5625 -40.2693)))
(apply 'command (append '("pline") coords '("c")))
(setq currobj (ssadd (entlast) currobj))
(command "_layer" "set" "nitride" "")
(command "_layer" "set" "fda1" "")
(setq coords (list 
(list 1600.5625 -29.1263) 
(list 1674.585 -29.8763) 
(list 1674.585 -29.6993) 
(list 1600.5625 -29.0493)))
(apply 'command (append '("pline") coords '("c")))
(setq currobj (ssadd (entlast) currobj))
(setq coords (list 
(list 1600.5625 -28.9063) 
(list 1674.585 -29.5563) 
(list 1674.585 -29.3793) 
(list 1600.5625 -28.8293)))
(apply 'command (append '("pline") coords '("c")))
(setq currobj (ssadd (entlast) currobj))
(setq coords (list 
(list 1600.5625 -28.6863) 
(list 1674.585 -29.2363) 
(list 1674.585 -29.0593) 
(list 1600.5625 -28.6093)))
(apply 'command (append '("pline") coords '("c")))
(setq currobj (ssadd (entlast) currobj))
(setq coords (list 
(list 1600.5625 -28.4663) 
(list 1674.585 -28.9163) 
(list 1674.585 -28.7393) 
(list 1600.5625 -28.3893)))
(apply 'command (append '("pline") coords '("c")))
(setq currobj (ssadd (entlast) currobj))
(setq coords (list 
(list 1600.5625 -28.2463) 
(list 1674.585 -28.5963) 
(list 1674.585 -28.4193) 
(list 1600.5625 -28.1693)))
(apply 'command (append '("pline") coords '("c")))
(setq currobj (ssadd (entlast) currobj))
(setq coords (list 
(list 1600.5625 -28.0263) 
(list 1674.585 -28.2763) 
(list 1674.585 -28.0993) 
(list 1600.5625 -27.9493)))
(apply 'command (append '("pline") coords '("c")))
(setq currobj (ssadd (entlast) currobj))
(setq coords (list 
(list 1600.5625 -27.8063) 
(list 1674.585 -27.9563) 
(list 1674.585 -27.7793) 
(list 1600.5625 -27.7293)))
(apply 'command (append '("pline") coords '("c")))
(setq currobj (ssadd (entlast) currobj))
(setq coords (list 
(list 1600.5625 -27.5863) 
(list 1674.585 -27.6363) 
(list 1674.585 -27.4593) 
(list 1600.5625 -27.5093)))
(apply 'command (append '("pline") coords '("c")))
(setq currobj (ssadd (entlast) currobj))
(setq coords (list 
(list 1600.5625 -27.3663) 
(list 1674.585 -27.3163) 
(list 1674.585 -27.1393) 
(list 1600.5625 -27.2893)))
(apply 'command (append '("pline") coords '("c")))
(setq currobj (ssadd (entlast) currobj))
(setq coords (list 
(list 1600.5625 -27.1463) 
(list 1674.585 -26.9963) 
(list 1674.585 -26.8193) 
(list 1600.5625 -27.0693)))
(apply 'command (append '("pline") coords '("c")))
(setq currobj (ssadd (entlast) currobj))
(setq coords (list 
(list 1600.5625 -26.9263) 
(list 1674.585 -26.6763) 
(list 1674.585 -26.4993) 
(list 1600.5625 -26.8493)))
(apply 'command (append '("pline") coords '("c")))
(setq currobj (ssadd (entlast) currobj))
(setq coords (list 
(list 1600.5625 -26.7063) 
(list 1674.585 -26.3563) 
(list 1674.585 -26.1793) 
(list 1600.5625 -26.6293)))
(apply 'command (append '("pline") coords '("c")))
(setq currobj (ssadd (entlast) currobj))
(setq coords (list 
(list 1600.5625 -26.4863) 
(list 1674.585 -26.0363) 
(list 1674.585 -25.8593) 
(list 1600.5625 -26.4093)))
(apply 'command (append '("pline") coords '("c")))
(setq currobj (ssadd (entlast) currobj))
(setq coords (list 
(list 1600.5625 -26.2663) 
(list 1674.585 -25.7163) 
(list 1674.585 -25.5393) 
(list 1600.5625 -26.1893)))
(apply 'command (append '("pline") coords '("c")))
(setq currobj (ssadd (entlast) currobj))
(setq coords (list 
(list 1600.5625 -26.0463) 
(list 1674.585 -25.3963) 
(list 1674.585 -25.2193) 
(list 1600.5625 -25.9693)))
(apply 'command (append '("pline") coords '("c")))
(setq currobj (ssadd (entlast) currobj))
(setq coords (list 
(list 1599.4375 -25.9693) 
(list 1525.415 -25.2193) 
(list 1525.415 -25.3963) 
(list 1599.4375 -26.0463)))
(apply 'command (append '("pline") coords '("c")))
(setq currobj (ssadd (entlast) currobj))
(setq coords (list 
(list 1599.4375 -26.1893) 
(list 1525.415 -25.5393) 
(list 1525.415 -25.7163) 
(list 1599.4375 -26.2663)))
(apply 'command (append '("pline") coords '("c")))
(setq currobj (ssadd (entlast) currobj))
(setq coords (list 
(list 1599.4375 -26.4093) 
(list 1525.415 -25.8593) 
(list 1525.415 -26.0363) 
(list 1599.4375 -26.4863)))
(apply 'command (append '("pline") coords '("c")))
(setq currobj (ssadd (entlast) currobj))
(setq coords (list 
(list 1599.4375 -26.6293) 
(list 1525.415 -26.1793) 
(list 1525.415 -26.3563) 
(list 1599.4375 -26.7063)))
(apply 'command (append '("pline") coords '("c")))
(setq currobj (ssadd (entlast) currobj))
(setq coords (list 
(list 1599.4375 -26.8493) 
(list 1525.415 -26.4993) 
(list 1525.415 -26.6763) 
(list 1599.4375 -26.9263)))
(apply 'command (append '("pline") coords '("c")))
(setq currobj (ssadd (entlast) currobj))
(setq coords (list 
(list 1599.4375 -27.0693) 
(list 1525.415 -26.8193) 
(list 1525.415 -26.9963) 
(list 1599.4375 -27.1463)))
(apply 'command (append '("pline") coords '("c")))
(setq currobj (ssadd (entlast) currobj))
(setq coords (list 
(list 1599.4375 -27.2893) 
(list 1525.415 -27.1393) 
(list 1525.415 -27.3163) 
(list 1599.4375 -27.3663)))
(apply 'command (append '("pline") coords '("c")))
(setq currobj (ssadd (entlast) currobj))
(setq coords (list 
(list 1599.4375 -27.5093) 
(list 1525.415 -27.4593) 
(list 1525.415 -27.6363) 
(list 1599.4375 -27.5863)))
(apply 'command (append '("pline") coords '("c")))
(setq currobj (ssadd (entlast) currobj))
(setq coords (list 
(list 1599.4375 -27.7293) 
(list 1525.415 -27.7793) 
(list 1525.415 -27.9563) 
(list 1599.4375 -27.8063)))
(apply 'command (append '("pline") coords '("c")))
(setq currobj (ssadd (entlast) currobj))
(setq coords (list 
(list 1599.4375 -27.9493) 
(list 1525.415 -28.0993) 
(list 1525.415 -28.2763) 
(list 1599.4375 -28.0263)))
(apply 'command (append '("pline") coords '("c")))
(setq currobj (ssadd (entlast) currobj))
(setq coords (list 
(list 1599.4375 -28.1693) 
(list 1525.415 -28.4193) 
(list 1525.415 -28.5963) 
(list 1599.4375 -28.2463)))
(apply 'command (append '("pline") coords '("c")))
(setq currobj (ssadd (entlast) currobj))
(setq coords (list 
(list 1599.4375 -28.3893) 
(list 1525.415 -28.7393) 
(list 1525.415 -28.9163) 
(list 1599.4375 -28.4663)))
(apply 'command (append '("pline") coords '("c")))
(setq currobj (ssadd (entlast) currobj))
(setq coords (list 
(list 1599.4375 -28.6093) 
(list 1525.415 -29.0593) 
(list 1525.415 -29.2363) 
(list 1599.4375 -28.6863)))
(apply 'command (append '("pline") coords '("c")))
(setq currobj (ssadd (entlast) currobj))
(setq coords (list 
(list 1599.4375 -28.8293) 
(list 1525.415 -29.3793) 
(list 1525.415 -29.5563) 
(list 1599.4375 -28.9063)))
(apply 'command (append '("pline") coords '("c")))
(setq currobj (ssadd (entlast) currobj))
(setq coords (list 
(list 1599.4375 -29.0493) 
(list 1525.415 -29.6993) 
(list 1525.415 -29.8763) 
(list 1599.4375 -29.1263)))
(apply 'command (append '("pline") coords '("c")))
(setq currobj (ssadd (entlast) currobj))
(command "_layer" "set" "nitride" "")
(command "_layer" "set" "text" "")
(command "_circle" "1599.0625,-40.2693" "0.075")
(command "_circle" "1599.0625,-39.9693" "0.075")
(command "_circle" "1599.0625,-39.6693" "0.075")
(command "_circle" "1599.0625,-39.3693" "0.075")
(command "_circle" "1599.0625,-39.0693" "0.075")
(command "_circle" "1598.7625,-40.2693" "0.075")
(command "_circle" "1598.7625,-39.9693" "0.075")
(command "_circle" "1598.7625,-39.6693" "0.075")
(command "_circle" "1598.7625,-39.3693" "0.075")
(command "_circle" "1598.7625,-39.0693" "0.075")
(command "_circle" "1598.4625,-40.2693" "0.075")
(command "_circle" "1598.4625,-39.9693" "0.075")
(command "_circle" "1598.4625,-39.6693" "0.075")
(command "_circle" "1598.4625,-39.3693" "0.075")
(command "_circle" "1598.4625,-39.0693" "0.075")
(command "_circle" "1598.1625,-40.2693" "0.075")
(command "_circle" "1598.1625,-39.9693" "0.075")
(command "_circle" "1598.1625,-39.6693" "0.075")
(command "_circle" "1598.1625,-39.3693" "0.075")
(command "_circle" "1598.1625,-39.0693" "0.075")
(command "_circle" "1597.8625,-40.2693" "0.075")
(command "_circle" "1597.8625,-39.9693" "0.075")
(command "_circle" "1597.8625,-39.6693" "0.075")
(command "_circle" "1597.8625,-39.3693" "0.075")
(command "_circle" "1597.8625,-39.0693" "0.075")
(command "_layer" "set" "nitride" "")
(setq coords (list 
(list 1600.2625 -14.8263) 
(list 1600.2625 100.8184) 
(list 1599.7375 100.8184) 
(list 1599.7375 -14.8263)))
(apply 'command (append '("pline") coords '("c")))
(setq currobj (ssadd (entlast) currobj))
(command "_layer" "set" "prebias" "")
(command "_rectangle" "1599.7375,-14.8263" "1600.2625,100.8184")
(setq currobj (ssadd (entlast) currobj))
(command "_layer" "set" "nitride" "")
(setq coords (list 
(list 1600.2625 100.8184) 
(list 1600.5625 110.8184) 
(list 1600.5625 110.8184) 
(list 1600.5625 111.8184) 
(list 1674.585 111.0684) 
(list 1674.585 116.0114) 
(list 1600.5625 115.2614) 
(list 1600.5625 116.2614) 
(list 1600.5625 116.2614) 
(list 1600.2625 126.2614) 
(list 1599.7375 126.2614) 
(list 1599.4375 116.2614) 
(list 1599.4375 116.2614) 
(list 1599.4375 115.2614) 
(list 1525.415 116.0114) 
(list 1525.415 111.0684) 
(list 1599.4375 111.8184) 
(list 1599.4375 110.8184) 
(list 1599.4375 110.8184) 
(list 1599.7375 100.8184)))
(apply 'command (append '("pline") coords '("c")))
(setq currobj (ssadd (entlast) currobj))
(command "_layer" "set" "prebias" "")
(setq coords (list 
(list 1599.4375 100.8184) 
(list 1599.4375 111.8184) 
(list 1525.415 111.0684) 
(list 1525.415 116.0114) 
(list 1599.4375 115.2614) 
(list 1599.4375 126.2614) 
(list 1600.5625 126.2614) 
(list 1600.5625 115.2614) 
(list 1674.585 116.0114) 
(list 1674.585 111.0684) 
(list 1600.5625 111.8184) 
(list 1600.5625 100.8184)))
(apply 'command (append '("pline") coords '("c")))
(setq currobj (ssadd (entlast) currobj))
(command "_layer" "set" "nitride" "")
(command "_layer" "set" "fda1" "")
(setq coords (list 
(list 1600.5625 111.9614) 
(list 1674.585 111.2114) 
(list 1674.585 111.3884) 
(list 1600.5625 112.0384)))
(apply 'command (append '("pline") coords '("c")))
(setq currobj (ssadd (entlast) currobj))
(setq coords (list 
(list 1600.5625 112.1814) 
(list 1674.585 111.5314) 
(list 1674.585 111.7084) 
(list 1600.5625 112.2584)))
(apply 'command (append '("pline") coords '("c")))
(setq currobj (ssadd (entlast) currobj))
(setq coords (list 
(list 1600.5625 112.4014) 
(list 1674.585 111.8514) 
(list 1674.585 112.0284) 
(list 1600.5625 112.4784)))
(apply 'command (append '("pline") coords '("c")))
(setq currobj (ssadd (entlast) currobj))
(setq coords (list 
(list 1600.5625 112.6214) 
(list 1674.585 112.1714) 
(list 1674.585 112.3484) 
(list 1600.5625 112.6984)))
(apply 'command (append '("pline") coords '("c")))
(setq currobj (ssadd (entlast) currobj))
(setq coords (list 
(list 1600.5625 112.8414) 
(list 1674.585 112.4914) 
(list 1674.585 112.6684) 
(list 1600.5625 112.9184)))
(apply 'command (append '("pline") coords '("c")))
(setq currobj (ssadd (entlast) currobj))
(setq coords (list 
(list 1600.5625 113.0614) 
(list 1674.585 112.8114) 
(list 1674.585 112.9884) 
(list 1600.5625 113.1384)))
(apply 'command (append '("pline") coords '("c")))
(setq currobj (ssadd (entlast) currobj))
(setq coords (list 
(list 1600.5625 113.2814) 
(list 1674.585 113.1314) 
(list 1674.585 113.3084) 
(list 1600.5625 113.3584)))
(apply 'command (append '("pline") coords '("c")))
(setq currobj (ssadd (entlast) currobj))
(setq coords (list 
(list 1600.5625 113.5014) 
(list 1674.585 113.4514) 
(list 1674.585 113.6284) 
(list 1600.5625 113.5784)))
(apply 'command (append '("pline") coords '("c")))
(setq currobj (ssadd (entlast) currobj))
(setq coords (list 
(list 1600.5625 113.7214) 
(list 1674.585 113.7714) 
(list 1674.585 113.9484) 
(list 1600.5625 113.7984)))
(apply 'command (append '("pline") coords '("c")))
(setq currobj (ssadd (entlast) currobj))
(setq coords (list 
(list 1600.5625 113.9414) 
(list 1674.585 114.0914) 
(list 1674.585 114.2684) 
(list 1600.5625 114.0184)))
(apply 'command (append '("pline") coords '("c")))
(setq currobj (ssadd (entlast) currobj))
(setq coords (list 
(list 1600.5625 114.1614) 
(list 1674.585 114.4114) 
(list 1674.585 114.5884) 
(list 1600.5625 114.2384)))
(apply 'command (append '("pline") coords '("c")))
(setq currobj (ssadd (entlast) currobj))
(setq coords (list 
(list 1600.5625 114.3814) 
(list 1674.585 114.7314) 
(list 1674.585 114.9084) 
(list 1600.5625 114.4584)))
(apply 'command (append '("pline") coords '("c")))
(setq currobj (ssadd (entlast) currobj))
(setq coords (list 
(list 1600.5625 114.6014) 
(list 1674.585 115.0514) 
(list 1674.585 115.2284) 
(list 1600.5625 114.6784)))
(apply 'command (append '("pline") coords '("c")))
(setq currobj (ssadd (entlast) currobj))
(setq coords (list 
(list 1600.5625 114.8214) 
(list 1674.585 115.3714) 
(list 1674.585 115.5484) 
(list 1600.5625 114.8984)))
(apply 'command (append '("pline") coords '("c")))
(setq currobj (ssadd (entlast) currobj))
(setq coords (list 
(list 1600.5625 115.0414) 
(list 1674.585 115.6914) 
(list 1674.585 115.8684) 
(list 1600.5625 115.1184)))
(apply 'command (append '("pline") coords '("c")))
(setq currobj (ssadd (entlast) currobj))
(setq coords (list 
(list 1599.4375 115.1184) 
(list 1525.415 115.8684) 
(list 1525.415 115.6914) 
(list 1599.4375 115.0414)))
(apply 'command (append '("pline") coords '("c")))
(setq currobj (ssadd (entlast) currobj))
(setq coords (list 
(list 1599.4375 114.8984) 
(list 1525.415 115.5484) 
(list 1525.415 115.3714) 
(list 1599.4375 114.8214)))
(apply 'command (append '("pline") coords '("c")))
(setq currobj (ssadd (entlast) currobj))
(setq coords (list 
(list 1599.4375 114.6784) 
(list 1525.415 115.2284) 
(list 1525.415 115.0514) 
(list 1599.4375 114.6014)))
(apply 'command (append '("pline") coords '("c")))
(setq currobj (ssadd (entlast) currobj))
(setq coords (list 
(list 1599.4375 114.4584) 
(list 1525.415 114.9084) 
(list 1525.415 114.7314) 
(list 1599.4375 114.3814)))
(apply 'command (append '("pline") coords '("c")))
(setq currobj (ssadd (entlast) currobj))
(setq coords (list 
(list 1599.4375 114.2384) 
(list 1525.415 114.5884) 
(list 1525.415 114.4114) 
(list 1599.4375 114.1614)))
(apply 'command (append '("pline") coords '("c")))
(setq currobj (ssadd (entlast) currobj))
(setq coords (list 
(list 1599.4375 114.0184) 
(list 1525.415 114.2684) 
(list 1525.415 114.0914) 
(list 1599.4375 113.9414)))
(apply 'command (append '("pline") coords '("c")))
(setq currobj (ssadd (entlast) currobj))
(setq coords (list 
(list 1599.4375 113.7984) 
(list 1525.415 113.9484) 
(list 1525.415 113.7714) 
(list 1599.4375 113.7214)))
(apply 'command (append '("pline") coords '("c")))
(setq currobj (ssadd (entlast) currobj))
(setq coords (list 
(list 1599.4375 113.5784) 
(list 1525.415 113.6284) 
(list 1525.415 113.4514) 
(list 1599.4375 113.5014)))
(apply 'command (append '("pline") coords '("c")))
(setq currobj (ssadd (entlast) currobj))
(setq coords (list 
(list 1599.4375 113.3584) 
(list 1525.415 113.3084) 
(list 1525.415 113.1314) 
(list 1599.4375 113.2814)))
(apply 'command (append '("pline") coords '("c")))
(setq currobj (ssadd (entlast) currobj))
(setq coords (list 
(list 1599.4375 113.1384) 
(list 1525.415 112.9884) 
(list 1525.415 112.8114) 
(list 1599.4375 113.0614)))
(apply 'command (append '("pline") coords '("c")))
(setq currobj (ssadd (entlast) currobj))
(setq coords (list 
(list 1599.4375 112.9184) 
(list 1525.415 112.6684) 
(list 1525.415 112.4914) 
(list 1599.4375 112.8414)))
(apply 'command (append '("pline") coords '("c")))
(setq currobj (ssadd (entlast) currobj))
(setq coords (list 
(list 1599.4375 112.6984) 
(list 1525.415 112.3484) 
(list 1525.415 112.1714) 
(list 1599.4375 112.6214)))
(apply 'command (append '("pline") coords '("c")))
(setq currobj (ssadd (entlast) currobj))
(setq coords (list 
(list 1599.4375 112.4784) 
(list 1525.415 112.0284) 
(list 1525.415 111.8514) 
(list 1599.4375 112.4014)))
(apply 'command (append '("pline") coords '("c")))
(setq currobj (ssadd (entlast) currobj))
(setq coords (list 
(list 1599.4375 112.2584) 
(list 1525.415 111.7084) 
(list 1525.415 111.5314) 
(list 1599.4375 112.1814)))
(apply 'command (append '("pline") coords '("c")))
(setq currobj (ssadd (entlast) currobj))
(setq coords (list 
(list 1599.4375 112.0384) 
(list 1525.415 111.3884) 
(list 1525.415 111.2114) 
(list 1599.4375 111.9614)))
(apply 'command (append '("pline") coords '("c")))
(setq currobj (ssadd (entlast) currobj))
(command "_layer" "set" "nitride" "")
(command "_layer" "set" "text" "")
(command "_circle" "1599.0625,100.8184" "0.075")
(command "_circle" "1599.0625,101.1184" "0.075")
(command "_circle" "1599.0625,101.4184" "0.075")
(command "_circle" "1599.0625,101.7184" "0.075")
(command "_circle" "1599.0625,102.0184" "0.075")
(command "_circle" "1598.7625,100.8184" "0.075")
(command "_circle" "1598.7625,101.1184" "0.075")
(command "_circle" "1598.7625,101.4184" "0.075")
(command "_circle" "1598.7625,101.7184" "0.075")
(command "_circle" "1598.7625,102.0184" "0.075")
(command "_circle" "1598.4625,100.8184" "0.075")
(command "_circle" "1598.4625,101.1184" "0.075")
(command "_circle" "1598.4625,101.4184" "0.075")
(command "_circle" "1598.4625,101.7184" "0.075")
(command "_circle" "1598.4625,102.0184" "0.075")
(command "_circle" "1598.1625,100.8184" "0.075")
(command "_circle" "1598.1625,101.1184" "0.075")
(command "_circle" "1598.1625,101.4184" "0.075")
(command "_circle" "1598.1625,101.7184" "0.075")
(command "_circle" "1598.1625,102.0184" "0.075")
(command "_circle" "1597.8625,100.8184" "0.075")
(command "_circle" "1597.8625,101.1184" "0.075")
(command "_circle" "1597.8625,101.4184" "0.075")
(command "_circle" "1597.8625,101.7184" "0.075")
(command "_circle" "1597.8625,102.0184" "0.075")
(command "_layer" "set" "nitride" "")
(setq coords (list 
(list 1600.2625 126.2614) 
(list 1600.2625 241.9061) 
(list 1599.7375 241.9061) 
(list 1599.7375 126.2614)))
(apply 'command (append '("pline") coords '("c")))
(setq currobj (ssadd (entlast) currobj))
(command "_layer" "set" "prebias" "")
(command "_rectangle" "1599.7375,126.2614" "1600.2625,241.9061")
(setq currobj (ssadd (entlast) currobj))
(command "_layer" "set" "nitride" "")
(setq coords (list 
(list 1600.2625 241.9061) 
(list 1600.5625 251.9061) 
(list 1600.5625 251.9061) 
(list 1600.5625 252.9061) 
(list 1674.585 252.1561) 
(list 1674.585 257.0991) 
(list 1600.5625 256.3491) 
(list 1600.5625 257.3491) 
(list 1600.5625 257.3491) 
(list 1600.2625 267.3491) 
(list 1599.7375 267.3491) 
(list 1599.4375 257.3491) 
(list 1599.4375 257.3491) 
(list 1599.4375 256.3491) 
(list 1525.415 257.0991) 
(list 1525.415 252.1561) 
(list 1599.4375 252.9061) 
(list 1599.4375 251.9061) 
(list 1599.4375 251.9061) 
(list 1599.7375 241.9061)))
(apply 'command (append '("pline") coords '("c")))
(setq currobj (ssadd (entlast) currobj))
(command "_layer" "set" "prebias" "")
(setq coords (list 
(list 1599.4375 241.9061) 
(list 1599.4375 252.9061) 
(list 1525.415 252.1561) 
(list 1525.415 257.0991) 
(list 1599.4375 256.3491) 
(list 1599.4375 267.3491) 
(list 1600.5625 267.3491) 
(list 1600.5625 256.3491) 
(list 1674.585 257.0991) 
(list 1674.585 252.1561) 
(list 1600.5625 252.9061) 
(list 1600.5625 241.9061)))
(apply 'command (append '("pline") coords '("c")))
(setq currobj (ssadd (entlast) currobj))
(command "_layer" "set" "nitride" "")
(command "_layer" "set" "fda1" "")
(setq coords (list 
(list 1600.5625 253.0491) 
(list 1674.585 252.2991) 
(list 1674.585 252.4761) 
(list 1600.5625 253.1261)))
(apply 'command (append '("pline") coords '("c")))
(setq currobj (ssadd (entlast) currobj))
(setq coords (list 
(list 1600.5625 253.2691) 
(list 1674.585 252.6191) 
(list 1674.585 252.7961) 
(list 1600.5625 253.3461)))
(apply 'command (append '("pline") coords '("c")))
(setq currobj (ssadd (entlast) currobj))
(setq coords (list 
(list 1600.5625 253.4891) 
(list 1674.585 252.9391) 
(list 1674.585 253.1161) 
(list 1600.5625 253.5661)))
(apply 'command (append '("pline") coords '("c")))
(setq currobj (ssadd (entlast) currobj))
(setq coords (list 
(list 1600.5625 253.7091) 
(list 1674.585 253.2591) 
(list 1674.585 253.4361) 
(list 1600.5625 253.7861)))
(apply 'command (append '("pline") coords '("c")))
(setq currobj (ssadd (entlast) currobj))
(setq coords (list 
(list 1600.5625 253.9291) 
(list 1674.585 253.5791) 
(list 1674.585 253.7561) 
(list 1600.5625 254.0061)))
(apply 'command (append '("pline") coords '("c")))
(setq currobj (ssadd (entlast) currobj))
(setq coords (list 
(list 1600.5625 254.1491) 
(list 1674.585 253.8991) 
(list 1674.585 254.0761) 
(list 1600.5625 254.2261)))
(apply 'command (append '("pline") coords '("c")))
(setq currobj (ssadd (entlast) currobj))
(setq coords (list 
(list 1600.5625 254.3691) 
(list 1674.585 254.2191) 
(list 1674.585 254.3961) 
(list 1600.5625 254.4461)))
(apply 'command (append '("pline") coords '("c")))
(setq currobj (ssadd (entlast) currobj))
(setq coords (list 
(list 1600.5625 254.5891) 
(list 1674.585 254.5391) 
(list 1674.585 254.7161) 
(list 1600.5625 254.6661)))
(apply 'command (append '("pline") coords '("c")))
(setq currobj (ssadd (entlast) currobj))
(setq coords (list 
(list 1600.5625 254.8091) 
(list 1674.585 254.8591) 
(list 1674.585 255.0361) 
(list 1600.5625 254.8861)))
(apply 'command (append '("pline") coords '("c")))
(setq currobj (ssadd (entlast) currobj))
(setq coords (list 
(list 1600.5625 255.0291) 
(list 1674.585 255.1791) 
(list 1674.585 255.3561) 
(list 1600.5625 255.1061)))
(apply 'command (append '("pline") coords '("c")))
(setq currobj (ssadd (entlast) currobj))
(setq coords (list 
(list 1600.5625 255.2491) 
(list 1674.585 255.4991) 
(list 1674.585 255.6761) 
(list 1600.5625 255.3261)))
(apply 'command (append '("pline") coords '("c")))
(setq currobj (ssadd (entlast) currobj))
(setq coords (list 
(list 1600.5625 255.4691) 
(list 1674.585 255.8191) 
(list 1674.585 255.9961) 
(list 1600.5625 255.5461)))
(apply 'command (append '("pline") coords '("c")))
(setq currobj (ssadd (entlast) currobj))
(setq coords (list 
(list 1600.5625 255.6891) 
(list 1674.585 256.1391) 
(list 1674.585 256.3161) 
(list 1600.5625 255.7661)))
(apply 'command (append '("pline") coords '("c")))
(setq currobj (ssadd (entlast) currobj))
(setq coords (list 
(list 1600.5625 255.9091) 
(list 1674.585 256.4591) 
(list 1674.585 256.6361) 
(list 1600.5625 255.9861)))
(apply 'command (append '("pline") coords '("c")))
(setq currobj (ssadd (entlast) currobj))
(setq coords (list 
(list 1600.5625 256.1291) 
(list 1674.585 256.7791) 
(list 1674.585 256.9561) 
(list 1600.5625 256.2061)))
(apply 'command (append '("pline") coords '("c")))
(setq currobj (ssadd (entlast) currobj))
(setq coords (list 
(list 1599.4375 256.2061) 
(list 1525.415 256.9561) 
(list 1525.415 256.7791) 
(list 1599.4375 256.1291)))
(apply 'command (append '("pline") coords '("c")))
(setq currobj (ssadd (entlast) currobj))
(setq coords (list 
(list 1599.4375 255.9861) 
(list 1525.415 256.6361) 
(list 1525.415 256.4591) 
(list 1599.4375 255.9091)))
(apply 'command (append '("pline") coords '("c")))
(setq currobj (ssadd (entlast) currobj))
(setq coords (list 
(list 1599.4375 255.7661) 
(list 1525.415 256.3161) 
(list 1525.415 256.1391) 
(list 1599.4375 255.6891)))
(apply 'command (append '("pline") coords '("c")))
(setq currobj (ssadd (entlast) currobj))
(setq coords (list 
(list 1599.4375 255.5461) 
(list 1525.415 255.9961) 
(list 1525.415 255.8191) 
(list 1599.4375 255.4691)))
(apply 'command (append '("pline") coords '("c")))
(setq currobj (ssadd (entlast) currobj))
(setq coords (list 
(list 1599.4375 255.3261) 
(list 1525.415 255.6761) 
(list 1525.415 255.4991) 
(list 1599.4375 255.2491)))
(apply 'command (append '("pline") coords '("c")))
(setq currobj (ssadd (entlast) currobj))
(setq coords (list 
(list 1599.4375 255.1061) 
(list 1525.415 255.3561) 
(list 1525.415 255.1791) 
(list 1599.4375 255.0291)))
(apply 'command (append '("pline") coords '("c")))
(setq currobj (ssadd (entlast) currobj))
(setq coords (list 
(list 1599.4375 254.8861) 
(list 1525.415 255.0361) 
(list 1525.415 254.8591) 
(list 1599.4375 254.8091)))
(apply 'command (append '("pline") coords '("c")))
(setq currobj (ssadd (entlast) currobj))
(setq coords (list 
(list 1599.4375 254.6661) 
(list 1525.415 254.7161) 
(list 1525.415 254.5391) 
(list 1599.4375 254.5891)))
(apply 'command (append '("pline") coords '("c")))
(setq currobj (ssadd (entlast) currobj))
(setq coords (list 
(list 1599.4375 254.4461) 
(list 1525.415 254.3961) 
(list 1525.415 254.2191) 
(list 1599.4375 254.3691)))
(apply 'command (append '("pline") coords '("c")))
(setq currobj (ssadd (entlast) currobj))
(setq coords (list 
(list 1599.4375 254.2261) 
(list 1525.415 254.0761) 
(list 1525.415 253.8991) 
(list 1599.4375 254.1491)))
(apply 'command (append '("pline") coords '("c")))
(setq currobj (ssadd (entlast) currobj))
(setq coords (list 
(list 1599.4375 254.0061) 
(list 1525.415 253.7561) 
(list 1525.415 253.5791) 
(list 1599.4375 253.9291)))
(apply 'command (append '("pline") coords '("c")))
(setq currobj (ssadd (entlast) currobj))
(setq coords (list 
(list 1599.4375 253.7861) 
(list 1525.415 253.4361) 
(list 1525.415 253.2591) 
(list 1599.4375 253.7091)))
(apply 'command (append '("pline") coords '("c")))
(setq currobj (ssadd (entlast) currobj))
(setq coords (list 
(list 1599.4375 253.5661) 
(list 1525.415 253.1161) 
(list 1525.415 252.9391) 
(list 1599.4375 253.4891)))
(apply 'command (append '("pline") coords '("c")))
(setq currobj (ssadd (entlast) currobj))
(setq coords (list 
(list 1599.4375 253.3461) 
(list 1525.415 252.7961) 
(list 1525.415 252.6191) 
(list 1599.4375 253.2691)))
(apply 'command (append '("pline") coords '("c")))
(setq currobj (ssadd (entlast) currobj))
(setq coords (list 
(list 1599.4375 253.1261) 
(list 1525.415 252.4761) 
(list 1525.415 252.2991) 
(list 1599.4375 253.0491)))
(apply 'command (append '("pline") coords '("c")))
(setq currobj (ssadd (entlast) currobj))
(command "_layer" "set" "nitride" "")
(command "_layer" "set" "text" "")
(command "_circle" "1599.0625,241.9061" "0.075")
(command "_circle" "1599.0625,242.2061" "0.075")
(command "_circle" "1599.0625,242.5061" "0.075")
(command "_circle" "1599.0625,242.8061" "0.075")
(command "_circle" "1599.0625,243.1061" "0.075")
(command "_circle" "1598.7625,241.9061" "0.075")
(command "_circle" "1598.7625,242.2061" "0.075")
(command "_circle" "1598.7625,242.5061" "0.075")
(command "_circle" "1598.7625,242.8061" "0.075")
(command "_circle" "1598.7625,243.1061" "0.075")
(command "_circle" "1598.4625,241.9061" "0.075")
(command "_circle" "1598.4625,242.2061" "0.075")
(command "_circle" "1598.4625,242.5061" "0.075")
(command "_circle" "1598.4625,242.8061" "0.075")
(command "_circle" "1598.4625,243.1061" "0.075")
(command "_circle" "1598.1625,241.9061" "0.075")
(command "_circle" "1598.1625,242.2061" "0.075")
(command "_circle" "1598.1625,242.5061" "0.075")
(command "_circle" "1598.1625,242.8061" "0.075")
(command "_circle" "1598.1625,243.1061" "0.075")
(command "_circle" "1597.8625,241.9061" "0.075")
(command "_circle" "1597.8625,242.2061" "0.075")
(command "_circle" "1597.8625,242.5061" "0.075")
(command "_circle" "1597.8625,242.8061" "0.075")
(command "_circle" "1597.8625,243.1061" "0.075")
(command "_layer" "set" "nitride" "")
(setq coords (list 
(list 1600.2625 267.3491) 
(list 1600.2625 382.9939) 
(list 1599.7375 382.9939) 
(list 1599.7375 267.3491)))
(apply 'command (append '("pline") coords '("c")))
(setq currobj (ssadd (entlast) currobj))
(command "_layer" "set" "prebias" "")
(command "_rectangle" "1599.7375,267.3491" "1600.2625,382.9939")
(setq currobj (ssadd (entlast) currobj))
(command "_layer" "set" "nitride" "")
(setq coords (list 
(list 1600.2625 382.9939) 
(list 1600.5625 392.9939) 
(list 1600.5625 392.9939) 
(list 1600.5625 393.9939) 
(list 1674.585 393.2439) 
(list 1674.585 398.1869) 
(list 1600.5625 397.4369) 
(list 1600.5625 398.4369) 
(list 1600.5625 398.4369) 
(list 1600.2625 408.4369) 
(list 1599.7375 408.4369) 
(list 1599.4375 398.4369) 
(list 1599.4375 398.4369) 
(list 1599.4375 397.4369) 
(list 1525.415 398.1869) 
(list 1525.415 393.2439) 
(list 1599.4375 393.9939) 
(list 1599.4375 392.9939) 
(list 1599.4375 392.9939) 
(list 1599.7375 382.9939)))
(apply 'command (append '("pline") coords '("c")))
(setq currobj (ssadd (entlast) currobj))
(command "_layer" "set" "prebias" "")
(setq coords (list 
(list 1599.4375 382.9939) 
(list 1599.4375 393.9939) 
(list 1525.415 393.2439) 
(list 1525.415 398.1869) 
(list 1599.4375 397.4369) 
(list 1599.4375 408.4369) 
(list 1600.5625 408.4369) 
(list 1600.5625 397.4369) 
(list 1674.585 398.1869) 
(list 1674.585 393.2439) 
(list 1600.5625 393.9939) 
(list 1600.5625 382.9939)))
(apply 'command (append '("pline") coords '("c")))
(setq currobj (ssadd (entlast) currobj))
(command "_layer" "set" "nitride" "")
(command "_layer" "set" "fda1" "")
(setq coords (list 
(list 1600.5625 394.1369) 
(list 1674.585 393.3869) 
(list 1674.585 393.5639) 
(list 1600.5625 394.2139)))
(apply 'command (append '("pline") coords '("c")))
(setq currobj (ssadd (entlast) currobj))
(setq coords (list 
(list 1600.5625 394.3569) 
(list 1674.585 393.7069) 
(list 1674.585 393.8839) 
(list 1600.5625 394.4339)))
(apply 'command (append '("pline") coords '("c")))
(setq currobj (ssadd (entlast) currobj))
(setq coords (list 
(list 1600.5625 394.5769) 
(list 1674.585 394.0269) 
(list 1674.585 394.2039) 
(list 1600.5625 394.6539)))
(apply 'command (append '("pline") coords '("c")))
(setq currobj (ssadd (entlast) currobj))
(setq coords (list 
(list 1600.5625 394.7969) 
(list 1674.585 394.3469) 
(list 1674.585 394.5239) 
(list 1600.5625 394.8739)))
(apply 'command (append '("pline") coords '("c")))
(setq currobj (ssadd (entlast) currobj))
(setq coords (list 
(list 1600.5625 395.0169) 
(list 1674.585 394.6669) 
(list 1674.585 394.8439) 
(list 1600.5625 395.0939)))
(apply 'command (append '("pline") coords '("c")))
(setq currobj (ssadd (entlast) currobj))
(setq coords (list 
(list 1600.5625 395.2369) 
(list 1674.585 394.9869) 
(list 1674.585 395.1639) 
(list 1600.5625 395.3139)))
(apply 'command (append '("pline") coords '("c")))
(setq currobj (ssadd (entlast) currobj))
(setq coords (list 
(list 1600.5625 395.4569) 
(list 1674.585 395.3069) 
(list 1674.585 395.4839) 
(list 1600.5625 395.5339)))
(apply 'command (append '("pline") coords '("c")))
(setq currobj (ssadd (entlast) currobj))
(setq coords (list 
(list 1600.5625 395.6769) 
(list 1674.585 395.6269) 
(list 1674.585 395.8039) 
(list 1600.5625 395.7539)))
(apply 'command (append '("pline") coords '("c")))
(setq currobj (ssadd (entlast) currobj))
(setq coords (list 
(list 1600.5625 395.8969) 
(list 1674.585 395.9469) 
(list 1674.585 396.1239) 
(list 1600.5625 395.9739)))
(apply 'command (append '("pline") coords '("c")))
(setq currobj (ssadd (entlast) currobj))
(setq coords (list 
(list 1600.5625 396.1169) 
(list 1674.585 396.2669) 
(list 1674.585 396.4439) 
(list 1600.5625 396.1939)))
(apply 'command (append '("pline") coords '("c")))
(setq currobj (ssadd (entlast) currobj))
(setq coords (list 
(list 1600.5625 396.3369) 
(list 1674.585 396.5869) 
(list 1674.585 396.7639) 
(list 1600.5625 396.4139)))
(apply 'command (append '("pline") coords '("c")))
(setq currobj (ssadd (entlast) currobj))
(setq coords (list 
(list 1600.5625 396.5569) 
(list 1674.585 396.9069) 
(list 1674.585 397.0839) 
(list 1600.5625 396.6339)))
(apply 'command (append '("pline") coords '("c")))
(setq currobj (ssadd (entlast) currobj))
(setq coords (list 
(list 1600.5625 396.7769) 
(list 1674.585 397.2269) 
(list 1674.585 397.4039) 
(list 1600.5625 396.8539)))
(apply 'command (append '("pline") coords '("c")))
(setq currobj (ssadd (entlast) currobj))
(setq coords (list 
(list 1600.5625 396.9969) 
(list 1674.585 397.5469) 
(list 1674.585 397.7239) 
(list 1600.5625 397.0739)))
(apply 'command (append '("pline") coords '("c")))
(setq currobj (ssadd (entlast) currobj))
(setq coords (list 
(list 1600.5625 397.2169) 
(list 1674.585 397.8669) 
(list 1674.585 398.0439) 
(list 1600.5625 397.2939)))
(apply 'command (append '("pline") coords '("c")))
(setq currobj (ssadd (entlast) currobj))
(setq coords (list 
(list 1599.4375 397.2939) 
(list 1525.415 398.0439) 
(list 1525.415 397.8669) 
(list 1599.4375 397.2169)))
(apply 'command (append '("pline") coords '("c")))
(setq currobj (ssadd (entlast) currobj))
(setq coords (list 
(list 1599.4375 397.0739) 
(list 1525.415 397.7239) 
(list 1525.415 397.5469) 
(list 1599.4375 396.9969)))
(apply 'command (append '("pline") coords '("c")))
(setq currobj (ssadd (entlast) currobj))
(setq coords (list 
(list 1599.4375 396.8539) 
(list 1525.415 397.4039) 
(list 1525.415 397.2269) 
(list 1599.4375 396.7769)))
(apply 'command (append '("pline") coords '("c")))
(setq currobj (ssadd (entlast) currobj))
(setq coords (list 
(list 1599.4375 396.6339) 
(list 1525.415 397.0839) 
(list 1525.415 396.9069) 
(list 1599.4375 396.5569)))
(apply 'command (append '("pline") coords '("c")))
(setq currobj (ssadd (entlast) currobj))
(setq coords (list 
(list 1599.4375 396.4139) 
(list 1525.415 396.7639) 
(list 1525.415 396.5869) 
(list 1599.4375 396.3369)))
(apply 'command (append '("pline") coords '("c")))
(setq currobj (ssadd (entlast) currobj))
(setq coords (list 
(list 1599.4375 396.1939) 
(list 1525.415 396.4439) 
(list 1525.415 396.2669) 
(list 1599.4375 396.1169)))
(apply 'command (append '("pline") coords '("c")))
(setq currobj (ssadd (entlast) currobj))
(setq coords (list 
(list 1599.4375 395.9739) 
(list 1525.415 396.1239) 
(list 1525.415 395.9469) 
(list 1599.4375 395.8969)))
(apply 'command (append '("pline") coords '("c")))
(setq currobj (ssadd (entlast) currobj))
(setq coords (list 
(list 1599.4375 395.7539) 
(list 1525.415 395.8039) 
(list 1525.415 395.6269) 
(list 1599.4375 395.6769)))
(apply 'command (append '("pline") coords '("c")))
(setq currobj (ssadd (entlast) currobj))
(setq coords (list 
(list 1599.4375 395.5339) 
(list 1525.415 395.4839) 
(list 1525.415 395.3069) 
(list 1599.4375 395.4569)))
(apply 'command (append '("pline") coords '("c")))
(setq currobj (ssadd (entlast) currobj))
(setq coords (list 
(list 1599.4375 395.3139) 
(list 1525.415 395.1639) 
(list 1525.415 394.9869) 
(list 1599.4375 395.2369)))
(apply 'command (append '("pline") coords '("c")))
(setq currobj (ssadd (entlast) currobj))
(setq coords (list 
(list 1599.4375 395.0939) 
(list 1525.415 394.8439) 
(list 1525.415 394.6669) 
(list 1599.4375 395.0169)))
(apply 'command (append '("pline") coords '("c")))
(setq currobj (ssadd (entlast) currobj))
(setq coords (list 
(list 1599.4375 394.8739) 
(list 1525.415 394.5239) 
(list 1525.415 394.3469) 
(list 1599.4375 394.7969)))
(apply 'command (append '("pline") coords '("c")))
(setq currobj (ssadd (entlast) currobj))
(setq coords (list 
(list 1599.4375 394.6539) 
(list 1525.415 394.2039) 
(list 1525.415 394.0269) 
(list 1599.4375 394.5769)))
(apply 'command (append '("pline") coords '("c")))
(setq currobj (ssadd (entlast) currobj))
(setq coords (list 
(list 1599.4375 394.4339) 
(list 1525.415 393.8839) 
(list 1525.415 393.7069) 
(list 1599.4375 394.3569)))
(apply 'command (append '("pline") coords '("c")))
(setq currobj (ssadd (entlast) currobj))
(setq coords (list 
(list 1599.4375 394.2139) 
(list 1525.415 393.5639) 
(list 1525.415 393.3869) 
(list 1599.4375 394.1369)))
(apply 'command (append '("pline") coords '("c")))
(setq currobj (ssadd (entlast) currobj))
(command "_layer" "set" "nitride" "")
(command "_layer" "set" "text" "")
(command "_circle" "1599.0625,382.9939" "0.075")
(command "_circle" "1599.0625,383.2939" "0.075")
(command "_circle" "1599.0625,383.5939" "0.075")
(command "_circle" "1599.0625,383.8939" "0.075")
(command "_circle" "1599.0625,384.1939" "0.075")
(command "_circle" "1598.7625,382.9939" "0.075")
(command "_circle" "1598.7625,383.2939" "0.075")
(command "_circle" "1598.7625,383.5939" "0.075")
(command "_circle" "1598.7625,383.8939" "0.075")
(command "_circle" "1598.7625,384.1939" "0.075")
(command "_circle" "1598.4625,382.9939" "0.075")
(command "_circle" "1598.4625,383.2939" "0.075")
(command "_circle" "1598.4625,383.5939" "0.075")
(command "_circle" "1598.4625,383.8939" "0.075")
(command "_circle" "1598.4625,384.1939" "0.075")
(command "_circle" "1598.1625,382.9939" "0.075")
(command "_circle" "1598.1625,383.2939" "0.075")
(command "_circle" "1598.1625,383.5939" "0.075")
(command "_circle" "1598.1625,383.8939" "0.075")
(command "_circle" "1598.1625,384.1939" "0.075")
(command "_circle" "1597.8625,382.9939" "0.075")
(command "_circle" "1597.8625,383.2939" "0.075")
(command "_circle" "1597.8625,383.5939" "0.075")
(command "_circle" "1597.8625,383.8939" "0.075")
(command "_circle" "1597.8625,384.1939" "0.075")
(command "_layer" "set" "nitride" "")
(setq coords (list 
(list 1600.2625 408.4369) 
(list 1600.2625 524.0816) 
(list 1599.7375 524.0816) 
(list 1599.7375 408.4369)))
(apply 'command (append '("pline") coords '("c")))
(setq currobj (ssadd (entlast) currobj))
(command "_layer" "set" "prebias" "")
(command "_rectangle" "1599.7375,408.4369" "1600.2625,524.0816")
(setq currobj (ssadd (entlast) currobj))
(command "_layer" "set" "nitride" "")
(setq coords (list 
(list 1600.2625 524.0816) 
(list 1600.5625 534.0816) 
(list 1600.5625 534.0816) 
(list 1600.5625 535.0816) 
(list 1674.585 534.3316) 
(list 1674.585 539.2746) 
(list 1600.5625 538.5246) 
(list 1600.5625 539.5246) 
(list 1600.5625 539.5246) 
(list 1600.2625 549.5246) 
(list 1599.7375 549.5246) 
(list 1599.4375 539.5246) 
(list 1599.4375 539.5246) 
(list 1599.4375 538.5246) 
(list 1525.415 539.2746) 
(list 1525.415 534.3316) 
(list 1599.4375 535.0816) 
(list 1599.4375 534.0816) 
(list 1599.4375 534.0816) 
(list 1599.7375 524.0816)))
(apply 'command (append '("pline") coords '("c")))
(setq currobj (ssadd (entlast) currobj))
(command "_layer" "set" "prebias" "")
(setq coords (list 
(list 1599.4375 524.0816) 
(list 1599.4375 535.0816) 
(list 1525.415 534.3316) 
(list 1525.415 539.2746) 
(list 1599.4375 538.5246) 
(list 1599.4375 549.5246) 
(list 1600.5625 549.5246) 
(list 1600.5625 538.5246) 
(list 1674.585 539.2746) 
(list 1674.585 534.3316) 
(list 1600.5625 535.0816) 
(list 1600.5625 524.0816)))
(apply 'command (append '("pline") coords '("c")))
(setq currobj (ssadd (entlast) currobj))
(command "_layer" "set" "nitride" "")
(command "_layer" "set" "fda1" "")
(setq coords (list 
(list 1600.5625 535.2246) 
(list 1674.585 534.4746) 
(list 1674.585 534.6516) 
(list 1600.5625 535.3016)))
(apply 'command (append '("pline") coords '("c")))
(setq currobj (ssadd (entlast) currobj))
(setq coords (list 
(list 1600.5625 535.4446) 
(list 1674.585 534.7946) 
(list 1674.585 534.9716) 
(list 1600.5625 535.5216)))
(apply 'command (append '("pline") coords '("c")))
(setq currobj (ssadd (entlast) currobj))
(setq coords (list 
(list 1600.5625 535.6646) 
(list 1674.585 535.1146) 
(list 1674.585 535.2916) 
(list 1600.5625 535.7416)))
(apply 'command (append '("pline") coords '("c")))
(setq currobj (ssadd (entlast) currobj))
(setq coords (list 
(list 1600.5625 535.8846) 
(list 1674.585 535.4346) 
(list 1674.585 535.6116) 
(list 1600.5625 535.9616)))
(apply 'command (append '("pline") coords '("c")))
(setq currobj (ssadd (entlast) currobj))
(setq coords (list 
(list 1600.5625 536.1046) 
(list 1674.585 535.7546) 
(list 1674.585 535.9316) 
(list 1600.5625 536.1816)))
(apply 'command (append '("pline") coords '("c")))
(setq currobj (ssadd (entlast) currobj))
(setq coords (list 
(list 1600.5625 536.3246) 
(list 1674.585 536.0746) 
(list 1674.585 536.2516) 
(list 1600.5625 536.4016)))
(apply 'command (append '("pline") coords '("c")))
(setq currobj (ssadd (entlast) currobj))
(setq coords (list 
(list 1600.5625 536.5446) 
(list 1674.585 536.3946) 
(list 1674.585 536.5716) 
(list 1600.5625 536.6216)))
(apply 'command (append '("pline") coords '("c")))
(setq currobj (ssadd (entlast) currobj))
(setq coords (list 
(list 1600.5625 536.7646) 
(list 1674.585 536.7146) 
(list 1674.585 536.8916) 
(list 1600.5625 536.8416)))
(apply 'command (append '("pline") coords '("c")))
(setq currobj (ssadd (entlast) currobj))
(setq coords (list 
(list 1600.5625 536.9846) 
(list 1674.585 537.0346) 
(list 1674.585 537.2116) 
(list 1600.5625 537.0616)))
(apply 'command (append '("pline") coords '("c")))
(setq currobj (ssadd (entlast) currobj))
(setq coords (list 
(list 1600.5625 537.2046) 
(list 1674.585 537.3546) 
(list 1674.585 537.5316) 
(list 1600.5625 537.2816)))
(apply 'command (append '("pline") coords '("c")))
(setq currobj (ssadd (entlast) currobj))
(setq coords (list 
(list 1600.5625 537.4246) 
(list 1674.585 537.6746) 
(list 1674.585 537.8516) 
(list 1600.5625 537.5016)))
(apply 'command (append '("pline") coords '("c")))
(setq currobj (ssadd (entlast) currobj))
(setq coords (list 
(list 1600.5625 537.6446) 
(list 1674.585 537.9946) 
(list 1674.585 538.1716) 
(list 1600.5625 537.7216)))
(apply 'command (append '("pline") coords '("c")))
(setq currobj (ssadd (entlast) currobj))
(setq coords (list 
(list 1600.5625 537.8646) 
(list 1674.585 538.3146) 
(list 1674.585 538.4916) 
(list 1600.5625 537.9416)))
(apply 'command (append '("pline") coords '("c")))
(setq currobj (ssadd (entlast) currobj))
(setq coords (list 
(list 1600.5625 538.0846) 
(list 1674.585 538.6346) 
(list 1674.585 538.8116) 
(list 1600.5625 538.1616)))
(apply 'command (append '("pline") coords '("c")))
(setq currobj (ssadd (entlast) currobj))
(setq coords (list 
(list 1600.5625 538.3046) 
(list 1674.585 538.9546) 
(list 1674.585 539.1316) 
(list 1600.5625 538.3816)))
(apply 'command (append '("pline") coords '("c")))
(setq currobj (ssadd (entlast) currobj))
(setq coords (list 
(list 1599.4375 538.3816) 
(list 1525.415 539.1316) 
(list 1525.415 538.9546) 
(list 1599.4375 538.3046)))
(apply 'command (append '("pline") coords '("c")))
(setq currobj (ssadd (entlast) currobj))
(setq coords (list 
(list 1599.4375 538.1616) 
(list 1525.415 538.8116) 
(list 1525.415 538.6346) 
(list 1599.4375 538.0846)))
(apply 'command (append '("pline") coords '("c")))
(setq currobj (ssadd (entlast) currobj))
(setq coords (list 
(list 1599.4375 537.9416) 
(list 1525.415 538.4916) 
(list 1525.415 538.3146) 
(list 1599.4375 537.8646)))
(apply 'command (append '("pline") coords '("c")))
(setq currobj (ssadd (entlast) currobj))
(setq coords (list 
(list 1599.4375 537.7216) 
(list 1525.415 538.1716) 
(list 1525.415 537.9946) 
(list 1599.4375 537.6446)))
(apply 'command (append '("pline") coords '("c")))
(setq currobj (ssadd (entlast) currobj))
(setq coords (list 
(list 1599.4375 537.5016) 
(list 1525.415 537.8516) 
(list 1525.415 537.6746) 
(list 1599.4375 537.4246)))
(apply 'command (append '("pline") coords '("c")))
(setq currobj (ssadd (entlast) currobj))
(setq coords (list 
(list 1599.4375 537.2816) 
(list 1525.415 537.5316) 
(list 1525.415 537.3546) 
(list 1599.4375 537.2046)))
(apply 'command (append '("pline") coords '("c")))
(setq currobj (ssadd (entlast) currobj))
(setq coords (list 
(list 1599.4375 537.0616) 
(list 1525.415 537.2116) 
(list 1525.415 537.0346) 
(list 1599.4375 536.9846)))
(apply 'command (append '("pline") coords '("c")))
(setq currobj (ssadd (entlast) currobj))
(setq coords (list 
(list 1599.4375 536.8416) 
(list 1525.415 536.8916) 
(list 1525.415 536.7146) 
(list 1599.4375 536.7646)))
(apply 'command (append '("pline") coords '("c")))
(setq currobj (ssadd (entlast) currobj))
(setq coords (list 
(list 1599.4375 536.6216) 
(list 1525.415 536.5716) 
(list 1525.415 536.3946) 
(list 1599.4375 536.5446)))
(apply 'command (append '("pline") coords '("c")))
(setq currobj (ssadd (entlast) currobj))
(setq coords (list 
(list 1599.4375 536.4016) 
(list 1525.415 536.2516) 
(list 1525.415 536.0746) 
(list 1599.4375 536.3246)))
(apply 'command (append '("pline") coords '("c")))
(setq currobj (ssadd (entlast) currobj))
(setq coords (list 
(list 1599.4375 536.1816) 
(list 1525.415 535.9316) 
(list 1525.415 535.7546) 
(list 1599.4375 536.1046)))
(apply 'command (append '("pline") coords '("c")))
(setq currobj (ssadd (entlast) currobj))
(setq coords (list 
(list 1599.4375 535.9616) 
(list 1525.415 535.6116) 
(list 1525.415 535.4346) 
(list 1599.4375 535.8846)))
(apply 'command (append '("pline") coords '("c")))
(setq currobj (ssadd (entlast) currobj))
(setq coords (list 
(list 1599.4375 535.7416) 
(list 1525.415 535.2916) 
(list 1525.415 535.1146) 
(list 1599.4375 535.6646)))
(apply 'command (append '("pline") coords '("c")))
(setq currobj (ssadd (entlast) currobj))
(setq coords (list 
(list 1599.4375 535.5216) 
(list 1525.415 534.9716) 
(list 1525.415 534.7946) 
(list 1599.4375 535.4446)))
(apply 'command (append '("pline") coords '("c")))
(setq currobj (ssadd (entlast) currobj))
(setq coords (list 
(list 1599.4375 535.3016) 
(list 1525.415 534.6516) 
(list 1525.415 534.4746) 
(list 1599.4375 535.2246)))
(apply 'command (append '("pline") coords '("c")))
(setq currobj (ssadd (entlast) currobj))
(command "_layer" "set" "nitride" "")
(command "_layer" "set" "text" "")
(command "_circle" "1599.0625,524.0816" "0.075")
(command "_circle" "1599.0625,524.3816" "0.075")
(command "_circle" "1599.0625,524.6816" "0.075")
(command "_circle" "1599.0625,524.9816" "0.075")
(command "_circle" "1599.0625,525.2816" "0.075")
(command "_circle" "1598.7625,524.0816" "0.075")
(command "_circle" "1598.7625,524.3816" "0.075")
(command "_circle" "1598.7625,524.6816" "0.075")
(command "_circle" "1598.7625,524.9816" "0.075")
(command "_circle" "1598.7625,525.2816" "0.075")
(command "_circle" "1598.4625,524.0816" "0.075")
(command "_circle" "1598.4625,524.3816" "0.075")
(command "_circle" "1598.4625,524.6816" "0.075")
(command "_circle" "1598.4625,524.9816" "0.075")
(command "_circle" "1598.4625,525.2816" "0.075")
(command "_circle" "1598.1625,524.0816" "0.075")
(command "_circle" "1598.1625,524.3816" "0.075")
(command "_circle" "1598.1625,524.6816" "0.075")
(command "_circle" "1598.1625,524.9816" "0.075")
(command "_circle" "1598.1625,525.2816" "0.075")
(command "_circle" "1597.8625,524.0816" "0.075")
(command "_circle" "1597.8625,524.3816" "0.075")
(command "_circle" "1597.8625,524.6816" "0.075")
(command "_circle" "1597.8625,524.9816" "0.075")
(command "_circle" "1597.8625,525.2816" "0.075")
(command "_layer" "set" "nitride" "")
(setq coords (list 
(list 1600.2625 549.5246) 
(list 1600.2625 665.1693) 
(list 1599.7375 665.1693) 
(list 1599.7375 549.5246)))
(apply 'command (append '("pline") coords '("c")))
(setq currobj (ssadd (entlast) currobj))
(command "_layer" "set" "prebias" "")
(command "_rectangle" "1599.7375,549.5246" "1600.2625,665.1693")
(setq currobj (ssadd (entlast) currobj))
(command "_layer" "set" "nitride" "")
(setq coords (list 
(list 1600.2625 665.1693) 
(list 1600.5625 675.1693) 
(list 1600.5625 675.1693) 
(list 1600.5625 676.1693) 
(list 1674.585 675.4193) 
(list 1674.585 680.3623) 
(list 1600.5625 679.6123) 
(list 1600.5625 680.6123) 
(list 1600.5625 680.6123) 
(list 1600.2625 690.6123) 
(list 1599.7375 690.6123) 
(list 1599.4375 680.6123) 
(list 1599.4375 680.6123) 
(list 1599.4375 679.6123) 
(list 1525.415 680.3623) 
(list 1525.415 675.4193) 
(list 1599.4375 676.1693) 
(list 1599.4375 675.1693) 
(list 1599.4375 675.1693) 
(list 1599.7375 665.1693)))
(apply 'command (append '("pline") coords '("c")))
(setq currobj (ssadd (entlast) currobj))
(command "_layer" "set" "prebias" "")
(setq coords (list 
(list 1599.4375 665.1693) 
(list 1599.4375 676.1693) 
(list 1525.415 675.4193) 
(list 1525.415 680.3623) 
(list 1599.4375 679.6123) 
(list 1599.4375 690.6123) 
(list 1600.5625 690.6123) 
(list 1600.5625 679.6123) 
(list 1674.585 680.3623) 
(list 1674.585 675.4193) 
(list 1600.5625 676.1693) 
(list 1600.5625 665.1693)))
(apply 'command (append '("pline") coords '("c")))
(setq currobj (ssadd (entlast) currobj))
(command "_layer" "set" "nitride" "")
(command "_layer" "set" "fda1" "")
(setq coords (list 
(list 1600.5625 676.3123) 
(list 1674.585 675.5623) 
(list 1674.585 675.7393) 
(list 1600.5625 676.3893)))
(apply 'command (append '("pline") coords '("c")))
(setq currobj (ssadd (entlast) currobj))
(setq coords (list 
(list 1600.5625 676.5323) 
(list 1674.585 675.8823) 
(list 1674.585 676.0593) 
(list 1600.5625 676.6093)))
(apply 'command (append '("pline") coords '("c")))
(setq currobj (ssadd (entlast) currobj))
(setq coords (list 
(list 1600.5625 676.7523) 
(list 1674.585 676.2023) 
(list 1674.585 676.3793) 
(list 1600.5625 676.8293)))
(apply 'command (append '("pline") coords '("c")))
(setq currobj (ssadd (entlast) currobj))
(setq coords (list 
(list 1600.5625 676.9723) 
(list 1674.585 676.5223) 
(list 1674.585 676.6993) 
(list 1600.5625 677.0493)))
(apply 'command (append '("pline") coords '("c")))
(setq currobj (ssadd (entlast) currobj))
(setq coords (list 
(list 1600.5625 677.1923) 
(list 1674.585 676.8423) 
(list 1674.585 677.0193) 
(list 1600.5625 677.2693)))
(apply 'command (append '("pline") coords '("c")))
(setq currobj (ssadd (entlast) currobj))
(setq coords (list 
(list 1600.5625 677.4123) 
(list 1674.585 677.1623) 
(list 1674.585 677.3393) 
(list 1600.5625 677.4893)))
(apply 'command (append '("pline") coords '("c")))
(setq currobj (ssadd (entlast) currobj))
(setq coords (list 
(list 1600.5625 677.6323) 
(list 1674.585 677.4823) 
(list 1674.585 677.6593) 
(list 1600.5625 677.7093)))
(apply 'command (append '("pline") coords '("c")))
(setq currobj (ssadd (entlast) currobj))
(setq coords (list 
(list 1600.5625 677.8523) 
(list 1674.585 677.8023) 
(list 1674.585 677.9793) 
(list 1600.5625 677.9293)))
(apply 'command (append '("pline") coords '("c")))
(setq currobj (ssadd (entlast) currobj))
(setq coords (list 
(list 1600.5625 678.0723) 
(list 1674.585 678.1223) 
(list 1674.585 678.2993) 
(list 1600.5625 678.1493)))
(apply 'command (append '("pline") coords '("c")))
(setq currobj (ssadd (entlast) currobj))
(setq coords (list 
(list 1600.5625 678.2923) 
(list 1674.585 678.4423) 
(list 1674.585 678.6193) 
(list 1600.5625 678.3693)))
(apply 'command (append '("pline") coords '("c")))
(setq currobj (ssadd (entlast) currobj))
(setq coords (list 
(list 1600.5625 678.5123) 
(list 1674.585 678.7623) 
(list 1674.585 678.9393) 
(list 1600.5625 678.5893)))
(apply 'command (append '("pline") coords '("c")))
(setq currobj (ssadd (entlast) currobj))
(setq coords (list 
(list 1600.5625 678.7323) 
(list 1674.585 679.0823) 
(list 1674.585 679.2593) 
(list 1600.5625 678.8093)))
(apply 'command (append '("pline") coords '("c")))
(setq currobj (ssadd (entlast) currobj))
(setq coords (list 
(list 1600.5625 678.9523) 
(list 1674.585 679.4023) 
(list 1674.585 679.5793) 
(list 1600.5625 679.0293)))
(apply 'command (append '("pline") coords '("c")))
(setq currobj (ssadd (entlast) currobj))
(setq coords (list 
(list 1600.5625 679.1723) 
(list 1674.585 679.7223) 
(list 1674.585 679.8993) 
(list 1600.5625 679.2493)))
(apply 'command (append '("pline") coords '("c")))
(setq currobj (ssadd (entlast) currobj))
(setq coords (list 
(list 1600.5625 679.3923) 
(list 1674.585 680.0423) 
(list 1674.585 680.2193) 
(list 1600.5625 679.4693)))
(apply 'command (append '("pline") coords '("c")))
(setq currobj (ssadd (entlast) currobj))
(setq coords (list 
(list 1599.4375 679.4693) 
(list 1525.415 680.2193) 
(list 1525.415 680.0423) 
(list 1599.4375 679.3923)))
(apply 'command (append '("pline") coords '("c")))
(setq currobj (ssadd (entlast) currobj))
(setq coords (list 
(list 1599.4375 679.2493) 
(list 1525.415 679.8993) 
(list 1525.415 679.7223) 
(list 1599.4375 679.1723)))
(apply 'command (append '("pline") coords '("c")))
(setq currobj (ssadd (entlast) currobj))
(setq coords (list 
(list 1599.4375 679.0293) 
(list 1525.415 679.5793) 
(list 1525.415 679.4023) 
(list 1599.4375 678.9523)))
(apply 'command (append '("pline") coords '("c")))
(setq currobj (ssadd (entlast) currobj))
(setq coords (list 
(list 1599.4375 678.8093) 
(list 1525.415 679.2593) 
(list 1525.415 679.0823) 
(list 1599.4375 678.7323)))
(apply 'command (append '("pline") coords '("c")))
(setq currobj (ssadd (entlast) currobj))
(setq coords (list 
(list 1599.4375 678.5893) 
(list 1525.415 678.9393) 
(list 1525.415 678.7623) 
(list 1599.4375 678.5123)))
(apply 'command (append '("pline") coords '("c")))
(setq currobj (ssadd (entlast) currobj))
(setq coords (list 
(list 1599.4375 678.3693) 
(list 1525.415 678.6193) 
(list 1525.415 678.4423) 
(list 1599.4375 678.2923)))
(apply 'command (append '("pline") coords '("c")))
(setq currobj (ssadd (entlast) currobj))
(setq coords (list 
(list 1599.4375 678.1493) 
(list 1525.415 678.2993) 
(list 1525.415 678.1223) 
(list 1599.4375 678.0723)))
(apply 'command (append '("pline") coords '("c")))
(setq currobj (ssadd (entlast) currobj))
(setq coords (list 
(list 1599.4375 677.9293) 
(list 1525.415 677.9793) 
(list 1525.415 677.8023) 
(list 1599.4375 677.8523)))
(apply 'command (append '("pline") coords '("c")))
(setq currobj (ssadd (entlast) currobj))
(setq coords (list 
(list 1599.4375 677.7093) 
(list 1525.415 677.6593) 
(list 1525.415 677.4823) 
(list 1599.4375 677.6323)))
(apply 'command (append '("pline") coords '("c")))
(setq currobj (ssadd (entlast) currobj))
(setq coords (list 
(list 1599.4375 677.4893) 
(list 1525.415 677.3393) 
(list 1525.415 677.1623) 
(list 1599.4375 677.4123)))
(apply 'command (append '("pline") coords '("c")))
(setq currobj (ssadd (entlast) currobj))
(setq coords (list 
(list 1599.4375 677.2693) 
(list 1525.415 677.0193) 
(list 1525.415 676.8423) 
(list 1599.4375 677.1923)))
(apply 'command (append '("pline") coords '("c")))
(setq currobj (ssadd (entlast) currobj))
(setq coords (list 
(list 1599.4375 677.0493) 
(list 1525.415 676.6993) 
(list 1525.415 676.5223) 
(list 1599.4375 676.9723)))
(apply 'command (append '("pline") coords '("c")))
(setq currobj (ssadd (entlast) currobj))
(setq coords (list 
(list 1599.4375 676.8293) 
(list 1525.415 676.3793) 
(list 1525.415 676.2023) 
(list 1599.4375 676.7523)))
(apply 'command (append '("pline") coords '("c")))
(setq currobj (ssadd (entlast) currobj))
(setq coords (list 
(list 1599.4375 676.6093) 
(list 1525.415 676.0593) 
(list 1525.415 675.8823) 
(list 1599.4375 676.5323)))
(apply 'command (append '("pline") coords '("c")))
(setq currobj (ssadd (entlast) currobj))
(setq coords (list 
(list 1599.4375 676.3893) 
(list 1525.415 675.7393) 
(list 1525.415 675.5623) 
(list 1599.4375 676.3123)))
(apply 'command (append '("pline") coords '("c")))
(setq currobj (ssadd (entlast) currobj))
(command "_layer" "set" "nitride" "")
(command "_layer" "set" "text" "")
(command "_circle" "1599.0625,665.1693" "0.075")
(command "_circle" "1599.0625,665.4693" "0.075")
(command "_circle" "1599.0625,665.7693" "0.075")
(command "_circle" "1599.0625,666.0693" "0.075")
(command "_circle" "1599.0625,666.3693" "0.075")
(command "_circle" "1598.7625,665.1693" "0.075")
(command "_circle" "1598.7625,665.4693" "0.075")
(command "_circle" "1598.7625,665.7693" "0.075")
(command "_circle" "1598.7625,666.0693" "0.075")
(command "_circle" "1598.7625,666.3693" "0.075")
(command "_circle" "1598.4625,665.1693" "0.075")
(command "_circle" "1598.4625,665.4693" "0.075")
(command "_circle" "1598.4625,665.7693" "0.075")
(command "_circle" "1598.4625,666.0693" "0.075")
(command "_circle" "1598.4625,666.3693" "0.075")
(command "_circle" "1598.1625,665.1693" "0.075")
(command "_circle" "1598.1625,665.4693" "0.075")
(command "_circle" "1598.1625,665.7693" "0.075")
(command "_circle" "1598.1625,666.0693" "0.075")
(command "_circle" "1598.1625,666.3693" "0.075")
(command "_circle" "1597.8625,665.1693" "0.075")
(command "_circle" "1597.8625,665.4693" "0.075")
(command "_circle" "1597.8625,665.7693" "0.075")
(command "_circle" "1597.8625,666.0693" "0.075")
(command "_circle" "1597.8625,666.3693" "0.075")
(command "_layer" "set" "nitride" "")
(setq coords (list 
(list 1600.2625 690.6123) 
(list 1600.2625 806.257) 
(list 1599.7375 806.257) 
(list 1599.7375 690.6123)))
(apply 'command (append '("pline") coords '("c")))
(setq currobj (ssadd (entlast) currobj))
(command "_layer" "set" "prebias" "")
(command "_rectangle" "1599.7375,690.6123" "1600.2625,806.257")
(setq currobj (ssadd (entlast) currobj))
(command "_layer" "set" "nitride" "")
(setq coords (list 
(list 1600.2625 806.257) 
(list 1600.5625 816.257) 
(list 1600.5625 816.257) 
(list 1600.5625 817.257) 
(list 1674.585 816.507) 
(list 1674.585 821.45) 
(list 1600.5625 820.7) 
(list 1600.5625 821.7) 
(list 1600.5625 821.7) 
(list 1600.2625 831.7) 
(list 1599.7375 831.7) 
(list 1599.4375 821.7) 
(list 1599.4375 821.7) 
(list 1599.4375 820.7) 
(list 1525.415 821.45) 
(list 1525.415 816.507) 
(list 1599.4375 817.257) 
(list 1599.4375 816.257) 
(list 1599.4375 816.257) 
(list 1599.7375 806.257)))
(apply 'command (append '("pline") coords '("c")))
(setq currobj (ssadd (entlast) currobj))
(command "_layer" "set" "prebias" "")
(setq coords (list 
(list 1599.4375 806.257) 
(list 1599.4375 817.257) 
(list 1525.415 816.507) 
(list 1525.415 821.45) 
(list 1599.4375 820.7) 
(list 1599.4375 831.7) 
(list 1600.5625 831.7) 
(list 1600.5625 820.7) 
(list 1674.585 821.45) 
(list 1674.585 816.507) 
(list 1600.5625 817.257) 
(list 1600.5625 806.257)))
(apply 'command (append '("pline") coords '("c")))
(setq currobj (ssadd (entlast) currobj))
(command "_layer" "set" "nitride" "")
(command "_layer" "set" "fda1" "")
(setq coords (list 
(list 1600.5625 817.4) 
(list 1674.585 816.65) 
(list 1674.585 816.827) 
(list 1600.5625 817.477)))
(apply 'command (append '("pline") coords '("c")))
(setq currobj (ssadd (entlast) currobj))
(setq coords (list 
(list 1600.5625 817.62) 
(list 1674.585 816.97) 
(list 1674.585 817.147) 
(list 1600.5625 817.697)))
(apply 'command (append '("pline") coords '("c")))
(setq currobj (ssadd (entlast) currobj))
(setq coords (list 
(list 1600.5625 817.84) 
(list 1674.585 817.29) 
(list 1674.585 817.467) 
(list 1600.5625 817.917)))
(apply 'command (append '("pline") coords '("c")))
(setq currobj (ssadd (entlast) currobj))
(setq coords (list 
(list 1600.5625 818.06) 
(list 1674.585 817.61) 
(list 1674.585 817.787) 
(list 1600.5625 818.137)))
(apply 'command (append '("pline") coords '("c")))
(setq currobj (ssadd (entlast) currobj))
(setq coords (list 
(list 1600.5625 818.28) 
(list 1674.585 817.93) 
(list 1674.585 818.107) 
(list 1600.5625 818.357)))
(apply 'command (append '("pline") coords '("c")))
(setq currobj (ssadd (entlast) currobj))
(setq coords (list 
(list 1600.5625 818.5) 
(list 1674.585 818.25) 
(list 1674.585 818.427) 
(list 1600.5625 818.577)))
(apply 'command (append '("pline") coords '("c")))
(setq currobj (ssadd (entlast) currobj))
(setq coords (list 
(list 1600.5625 818.72) 
(list 1674.585 818.57) 
(list 1674.585 818.747) 
(list 1600.5625 818.797)))
(apply 'command (append '("pline") coords '("c")))
(setq currobj (ssadd (entlast) currobj))
(setq coords (list 
(list 1600.5625 818.94) 
(list 1674.585 818.89) 
(list 1674.585 819.067) 
(list 1600.5625 819.017)))
(apply 'command (append '("pline") coords '("c")))
(setq currobj (ssadd (entlast) currobj))
(setq coords (list 
(list 1600.5625 819.16) 
(list 1674.585 819.21) 
(list 1674.585 819.387) 
(list 1600.5625 819.237)))
(apply 'command (append '("pline") coords '("c")))
(setq currobj (ssadd (entlast) currobj))
(setq coords (list 
(list 1600.5625 819.38) 
(list 1674.585 819.53) 
(list 1674.585 819.707) 
(list 1600.5625 819.457)))
(apply 'command (append '("pline") coords '("c")))
(setq currobj (ssadd (entlast) currobj))
(setq coords (list 
(list 1600.5625 819.6) 
(list 1674.585 819.85) 
(list 1674.585 820.027) 
(list 1600.5625 819.677)))
(apply 'command (append '("pline") coords '("c")))
(setq currobj (ssadd (entlast) currobj))
(setq coords (list 
(list 1600.5625 819.82) 
(list 1674.585 820.17) 
(list 1674.585 820.347) 
(list 1600.5625 819.897)))
(apply 'command (append '("pline") coords '("c")))
(setq currobj (ssadd (entlast) currobj))
(setq coords (list 
(list 1600.5625 820.04) 
(list 1674.585 820.49) 
(list 1674.585 820.667) 
(list 1600.5625 820.117)))
(apply 'command (append '("pline") coords '("c")))
(setq currobj (ssadd (entlast) currobj))
(setq coords (list 
(list 1600.5625 820.26) 
(list 1674.585 820.81) 
(list 1674.585 820.987) 
(list 1600.5625 820.337)))
(apply 'command (append '("pline") coords '("c")))
(setq currobj (ssadd (entlast) currobj))
(setq coords (list 
(list 1600.5625 820.48) 
(list 1674.585 821.13) 
(list 1674.585 821.307) 
(list 1600.5625 820.557)))
(apply 'command (append '("pline") coords '("c")))
(setq currobj (ssadd (entlast) currobj))
(setq coords (list 
(list 1599.4375 820.557) 
(list 1525.415 821.307) 
(list 1525.415 821.13) 
(list 1599.4375 820.48)))
(apply 'command (append '("pline") coords '("c")))
(setq currobj (ssadd (entlast) currobj))
(setq coords (list 
(list 1599.4375 820.337) 
(list 1525.415 820.987) 
(list 1525.415 820.81) 
(list 1599.4375 820.26)))
(apply 'command (append '("pline") coords '("c")))
(setq currobj (ssadd (entlast) currobj))
(setq coords (list 
(list 1599.4375 820.117) 
(list 1525.415 820.667) 
(list 1525.415 820.49) 
(list 1599.4375 820.04)))
(apply 'command (append '("pline") coords '("c")))
(setq currobj (ssadd (entlast) currobj))
(setq coords (list 
(list 1599.4375 819.897) 
(list 1525.415 820.347) 
(list 1525.415 820.17) 
(list 1599.4375 819.82)))
(apply 'command (append '("pline") coords '("c")))
(setq currobj (ssadd (entlast) currobj))
(setq coords (list 
(list 1599.4375 819.677) 
(list 1525.415 820.027) 
(list 1525.415 819.85) 
(list 1599.4375 819.6)))
(apply 'command (append '("pline") coords '("c")))
(setq currobj (ssadd (entlast) currobj))
(setq coords (list 
(list 1599.4375 819.457) 
(list 1525.415 819.707) 
(list 1525.415 819.53) 
(list 1599.4375 819.38)))
(apply 'command (append '("pline") coords '("c")))
(setq currobj (ssadd (entlast) currobj))
(setq coords (list 
(list 1599.4375 819.237) 
(list 1525.415 819.387) 
(list 1525.415 819.21) 
(list 1599.4375 819.16)))
(apply 'command (append '("pline") coords '("c")))
(setq currobj (ssadd (entlast) currobj))
(setq coords (list 
(list 1599.4375 819.017) 
(list 1525.415 819.067) 
(list 1525.415 818.89) 
(list 1599.4375 818.94)))
(apply 'command (append '("pline") coords '("c")))
(setq currobj (ssadd (entlast) currobj))
(setq coords (list 
(list 1599.4375 818.797) 
(list 1525.415 818.747) 
(list 1525.415 818.57) 
(list 1599.4375 818.72)))
(apply 'command (append '("pline") coords '("c")))
(setq currobj (ssadd (entlast) currobj))
(setq coords (list 
(list 1599.4375 818.577) 
(list 1525.415 818.427) 
(list 1525.415 818.25) 
(list 1599.4375 818.5)))
(apply 'command (append '("pline") coords '("c")))
(setq currobj (ssadd (entlast) currobj))
(setq coords (list 
(list 1599.4375 818.357) 
(list 1525.415 818.107) 
(list 1525.415 817.93) 
(list 1599.4375 818.28)))
(apply 'command (append '("pline") coords '("c")))
(setq currobj (ssadd (entlast) currobj))
(setq coords (list 
(list 1599.4375 818.137) 
(list 1525.415 817.787) 
(list 1525.415 817.61) 
(list 1599.4375 818.06)))
(apply 'command (append '("pline") coords '("c")))
(setq currobj (ssadd (entlast) currobj))
(setq coords (list 
(list 1599.4375 817.917) 
(list 1525.415 817.467) 
(list 1525.415 817.29) 
(list 1599.4375 817.84)))
(apply 'command (append '("pline") coords '("c")))
(setq currobj (ssadd (entlast) currobj))
(setq coords (list 
(list 1599.4375 817.697) 
(list 1525.415 817.147) 
(list 1525.415 816.97) 
(list 1599.4375 817.62)))
(apply 'command (append '("pline") coords '("c")))
(setq currobj (ssadd (entlast) currobj))
(setq coords (list 
(list 1599.4375 817.477) 
(list 1525.415 816.827) 
(list 1525.415 816.65) 
(list 1599.4375 817.4)))
(apply 'command (append '("pline") coords '("c")))
(setq currobj (ssadd (entlast) currobj))
(command "_layer" "set" "nitride" "")
(command "_layer" "set" "text" "")
(command "_circle" "1599.0625,806.257" "0.075")
(command "_circle" "1599.0625,806.557" "0.075")
(command "_circle" "1599.0625,806.857" "0.075")
(command "_circle" "1599.0625,807.157" "0.075")
(command "_circle" "1599.0625,807.457" "0.075")
(command "_circle" "1598.7625,806.257" "0.075")
(command "_circle" "1598.7625,806.557" "0.075")
(command "_circle" "1598.7625,806.857" "0.075")
(command "_circle" "1598.7625,807.157" "0.075")
(command "_circle" "1598.7625,807.457" "0.075")
(command "_circle" "1598.4625,806.257" "0.075")
(command "_circle" "1598.4625,806.557" "0.075")
(command "_circle" "1598.4625,806.857" "0.075")
(command "_circle" "1598.4625,807.157" "0.075")
(command "_circle" "1598.4625,807.457" "0.075")
(command "_circle" "1598.1625,806.257" "0.075")
(command "_circle" "1598.1625,806.557" "0.075")
(command "_circle" "1598.1625,806.857" "0.075")
(command "_circle" "1598.1625,807.157" "0.075")
(command "_circle" "1598.1625,807.457" "0.075")
(command "_circle" "1597.8625,806.257" "0.075")
(command "_circle" "1597.8625,806.557" "0.075")
(command "_circle" "1597.8625,806.857" "0.075")
(command "_circle" "1597.8625,807.157" "0.075")
(command "_circle" "1597.8625,807.457" "0.075")
(command "_layer" "set" "nitride" "")
(setq coords (list 
(list 1600.2625 831.7) 
(list 1600.2625 836.7) 
(list 1599.7375 836.7) 
(list 1599.7375 831.7)))
(apply 'command (append '("pline") coords '("c")))
(setq currobj (ssadd (entlast) currobj))
(command "_layer" "set" "prebias" "")
(command "_rectangle" "1599.7375,831.7" "1600.2625,836.7")
(setq currobj (ssadd (entlast) currobj))
(command "_layer" "set" "nitride" "")
(setq cooledsinglenanobeam5 currobj)
(setq currobj nil)
(setq currobj (ssadd))
; DRAWING PHOTONIC CRYSTAL
(command "_layer" "set" "negYjunc" "")
(setq coords (list 
(list 1600.135 866.7) 
(list 1600 851.7) 
(list 1600 866.7)))
(apply 'command (append '("pline") coords '("c")))
(setq currobj (ssadd (entlast) currobj))
(setq coords (list 
(list 1600.2625 836.7) 
(list 1600.415 866.7) 
(list 1601.076 866.7) 
(list 1601.076 836.7)))
(apply 'command (append '("pline") coords '("c")))
(setq currobj (ssadd (entlast) currobj))
(setq coords (list 
(list 1599.865 866.7) 
(list 1600 851.7) 
(list 1600 866.7)))
(apply 'command (append '("pline") coords '("c")))
(setq currobj (ssadd (entlast) currobj))
(setq coords (list 
(list 1599.7375 836.7) 
(list 1599.585 866.7) 
(list 1598.924 866.7) 
(list 1598.924 836.7)))
(apply 'command (append '("pline") coords '("c")))
(setq currobj (ssadd (entlast) currobj))
(command "_layer" "set" "nitride" "")
(setq yjunction5 currobj)
(setq currobj nil)
(setq currobj (ssadd))
(setq tap5 nil)
(setq tap5 (ssadd))
(command "_layer" "set" "phc" "")
(setq coords (list 
(list 1600 866.7) 
(list 1600.135 866.7) 
(list 1600.135 866.7103) 
(list 1600.135 866.7206) 
(list 1600.135 866.7308) 
(list 1600.135 866.7411) 
(list 1600.135 866.7514) 
(list 1600.135 866.7617) 
(list 1600.135 866.7719) 
(list 1600.135 866.7822) 
(list 1600.135 866.7925) 
(list 1600.135 866.8028) 
(list 1600.135 866.8131) 
(list 1600.135 866.8233) 
(list 1600.135 866.8336) 
(list 1600.135 866.8439) 
(list 1600.135 866.8542) 
(list 1600.135 866.8644) 
(list 1600.135 866.8747) 
(list 1600.135 866.885) 
(list 1600.135 866.8953) 
(list 1600.135 866.9056) 
(list 1600.135 866.9158) 
(list 1600.135 866.9261) 
(list 1600.135 866.9364) 
(list 1600.135 866.9467) 
(list 1600.135 866.9569) 
(list 1600.135 866.9672) 
(list 1600.135 866.9775) 
(list 1600.135 866.9878) 
(list 1600.135 866.9981) 
(list 1600.135 867.0083) 
(list 1600.135 867.0186) 
(list 1600.135 867.0289) 
(list 1600.135 867.0392) 
(list 1600.135 867.0494) 
(list 1600.135 867.0597) 
(list 1600.135 867.07) 
(list 1600 867.07)))
(apply 'command (append '("pline") coords '("c")))
(setq tap5 (ssadd (entlast) tap5))
(command "_mirror" (entlast) "" "1600,900" "1600,901" "No")
(setq tap5 (ssadd (entlast) tap5))
(setq coords (list 
(list 1600.4232 866.7) 
(list 1600.415 866.7) 
(list 1600.4152 866.7103) 
(list 1600.4154 866.7206) 
(list 1600.4156 866.7308) 
(list 1600.4157 866.7411) 
(list 1600.4157 866.7514) 
(list 1600.4157 866.7617) 
(list 1600.4156 866.7719) 
(list 1600.4153 866.7822) 
(list 1600.415 866.7925) 
(list 1600.4146 866.8028) 
(list 1600.4142 866.8131) 
(list 1600.4137 866.8233) 
(list 1600.4131 866.8336) 
(list 1600.4126 866.8439) 
(list 1600.4121 866.8542) 
(list 1600.4116 866.8644) 
(list 1600.4112 866.8747) 
(list 1600.411 866.885) 
(list 1600.4108 866.8953) 
(list 1600.4108 866.9056) 
(list 1600.4109 866.9158) 
(list 1600.4112 866.9261) 
(list 1600.4117 866.9364) 
(list 1600.4123 866.9467) 
(list 1600.4131 866.9569) 
(list 1600.414 866.9672) 
(list 1600.4151 866.9775) 
(list 1600.4162 866.9878) 
(list 1600.4173 866.9981) 
(list 1600.4184 867.0083) 
(list 1600.4196 867.0186) 
(list 1600.4206 867.0289) 
(list 1600.4215 867.0392) 
(list 1600.4223 867.0494) 
(list 1600.4229 867.0597) 
(list 1600.4232 867.07) 
(list 1600.4232 867.07)))
(apply 'command (append '("pline") coords '("c")))
(setq tap5 (ssadd (entlast) tap5))
(command "_mirror" (entlast) "" "1600,900" "1600,901" "No")
(setq tap5 (ssadd (entlast) tap5))
(setq coords (list 
(list 1601.076 866.7) 
(list 1600.4232 866.7) 
(list 1600.4232 866.7103) 
(list 1600.4232 866.7206) 
(list 1600.4232 866.7308) 
(list 1600.4232 866.7411) 
(list 1600.4232 866.7514) 
(list 1600.4232 866.7617) 
(list 1600.4232 866.7719) 
(list 1600.4232 866.7822) 
(list 1600.4232 866.7925) 
(list 1600.4232 866.8028) 
(list 1600.4232 866.8131) 
(list 1600.4232 866.8233) 
(list 1600.4232 866.8336) 
(list 1600.4232 866.8439) 
(list 1600.4232 866.8542) 
(list 1600.4232 866.8644) 
(list 1600.4232 866.8747) 
(list 1600.4232 866.885) 
(list 1600.4232 866.8953) 
(list 1600.4232 866.9056) 
(list 1600.4232 866.9158) 
(list 1600.4232 866.9261) 
(list 1600.4232 866.9364) 
(list 1600.4232 866.9467) 
(list 1600.4232 866.9569) 
(list 1600.4232 866.9672) 
(list 1600.4232 866.9775) 
(list 1600.4232 866.9878) 
(list 1600.4232 866.9981) 
(list 1600.4232 867.0083) 
(list 1600.4232 867.0186) 
(list 1600.4232 867.0289) 
(list 1600.4232 867.0392) 
(list 1600.4232 867.0494) 
(list 1600.4232 867.0597) 
(list 1600.4232 867.07) 
(list 1601.076 867.07)))
(apply 'command (append '("pline") coords '("c")))
(setq tap5 (ssadd (entlast) tap5))
(command "_mirror" (entlast) "" "1600,900" "1600,901" "No")
(setq tap5 (ssadd (entlast) tap5))
(setq coords (list 
(list 1600 867.07) 
(list 1600.135 867.07) 
(list 1600.135 867.0803) 
(list 1600.135 867.0906) 
(list 1600.135 867.1008) 
(list 1600.135 867.1111) 
(list 1600.135 867.1214) 
(list 1600.135 867.1317) 
(list 1600.135 867.1419) 
(list 1600.135 867.1522) 
(list 1600.135 867.1625) 
(list 1600.135 867.1728) 
(list 1600.135 867.1831) 
(list 1600.135 867.1933) 
(list 1600.135 867.2036) 
(list 1600.135 867.2139) 
(list 1600.135 867.2242) 
(list 1600.135 867.2344) 
(list 1600.135 867.2447) 
(list 1600.135 867.255) 
(list 1600.135 867.2653) 
(list 1600.135 867.2756) 
(list 1600.135 867.2858) 
(list 1600.135 867.2961) 
(list 1600.135 867.3064) 
(list 1600.135 867.3167) 
(list 1600.135 867.3269) 
(list 1600.135 867.3372) 
(list 1600.135 867.3475) 
(list 1600.135 867.3578) 
(list 1600.135 867.3681) 
(list 1600.135 867.3783) 
(list 1600.135 867.3886) 
(list 1600.135 867.3989) 
(list 1600.135 867.4092) 
(list 1600.135 867.4194) 
(list 1600.135 867.4297) 
(list 1600.135 867.44) 
(list 1600 867.44)))
(apply 'command (append '("pline") coords '("c")))
(setq tap5 (ssadd (entlast) tap5))
(command "_mirror" (entlast) "" "1600,900" "1600,901" "No")
(setq tap5 (ssadd (entlast) tap5))
(setq coords (list 
(list 1600.4314 867.07) 
(list 1600.4232 867.07) 
(list 1600.4233 867.0803) 
(list 1600.4231 867.0906) 
(list 1600.4227 867.1008) 
(list 1600.422 867.1111) 
(list 1600.421 867.1214) 
(list 1600.4198 867.1317) 
(list 1600.4184 867.1419) 
(list 1600.4168 867.1522) 
(list 1600.4151 867.1625) 
(list 1600.4133 867.1728) 
(list 1600.4115 867.1831) 
(list 1600.4097 867.1933) 
(list 1600.408 867.2036) 
(list 1600.4064 867.2139) 
(list 1600.4051 867.2242) 
(list 1600.4041 867.2344) 
(list 1600.4033 867.2447) 
(list 1600.4029 867.255) 
(list 1600.4029 867.2653) 
(list 1600.4032 867.2756) 
(list 1600.404 867.2858) 
(list 1600.4051 867.2961) 
(list 1600.4065 867.3064) 
(list 1600.4083 867.3167) 
(list 1600.4104 867.3269) 
(list 1600.4127 867.3372) 
(list 1600.4151 867.3475) 
(list 1600.4176 867.3578) 
(list 1600.4201 867.3681) 
(list 1600.4226 867.3783) 
(list 1600.4249 867.3886) 
(list 1600.4269 867.3989) 
(list 1600.4286 867.4092) 
(list 1600.43 867.4194) 
(list 1600.4309 867.4297) 
(list 1600.4314 867.44) 
(list 1600.4314 867.44)))
(apply 'command (append '("pline") coords '("c")))
(setq tap5 (ssadd (entlast) tap5))
(command "_mirror" (entlast) "" "1600,900" "1600,901" "No")
(setq tap5 (ssadd (entlast) tap5))
(setq coords (list 
(list 1601.076 867.07) 
(list 1600.4314 867.07) 
(list 1600.4314 867.0803) 
(list 1600.4314 867.0906) 
(list 1600.4314 867.1008) 
(list 1600.4314 867.1111) 
(list 1600.4314 867.1214) 
(list 1600.4314 867.1317) 
(list 1600.4314 867.1419) 
(list 1600.4314 867.1522) 
(list 1600.4314 867.1625) 
(list 1600.4314 867.1728) 
(list 1600.4314 867.1831) 
(list 1600.4314 867.1933) 
(list 1600.4314 867.2036) 
(list 1600.4314 867.2139) 
(list 1600.4314 867.2242) 
(list 1600.4314 867.2344) 
(list 1600.4314 867.2447) 
(list 1600.4314 867.255) 
(list 1600.4314 867.2653) 
(list 1600.4314 867.2756) 
(list 1600.4314 867.2858) 
(list 1600.4314 867.2961) 
(list 1600.4314 867.3064) 
(list 1600.4314 867.3167) 
(list 1600.4314 867.3269) 
(list 1600.4314 867.3372) 
(list 1600.4314 867.3475) 
(list 1600.4314 867.3578) 
(list 1600.4314 867.3681) 
(list 1600.4314 867.3783) 
(list 1600.4314 867.3886) 
(list 1600.4314 867.3989) 
(list 1600.4314 867.4092) 
(list 1600.4314 867.4194) 
(list 1600.4314 867.4297) 
(list 1600.4314 867.44) 
(list 1601.076 867.44)))
(apply 'command (append '("pline") coords '("c")))
(setq tap5 (ssadd (entlast) tap5))
(command "_mirror" (entlast) "" "1600,900" "1600,901" "No")
(setq tap5 (ssadd (entlast) tap5))
(setq coords (list 
(list 1600 867.44) 
(list 1600.135 867.44) 
(list 1600.135 867.4503) 
(list 1600.135 867.4606) 
(list 1600.135 867.4708) 
(list 1600.135 867.4811) 
(list 1600.135 867.4914) 
(list 1600.135 867.5017) 
(list 1600.135 867.5119) 
(list 1600.135 867.5222) 
(list 1600.135 867.5325) 
(list 1600.135 867.5428) 
(list 1600.135 867.5531) 
(list 1600.135 867.5633) 
(list 1600.135 867.5736) 
(list 1600.135 867.5839) 
(list 1600.135 867.5942) 
(list 1600.135 867.6044) 
(list 1600.135 867.6147) 
(list 1600.135 867.625) 
(list 1600.135 867.6353) 
(list 1600.135 867.6456) 
(list 1600.135 867.6558) 
(list 1600.135 867.6661) 
(list 1600.135 867.6764) 
(list 1600.135 867.6867) 
(list 1600.135 867.6969) 
(list 1600.135 867.7072) 
(list 1600.135 867.7175) 
(list 1600.135 867.7278) 
(list 1600.135 867.7381) 
(list 1600.135 867.7483) 
(list 1600.135 867.7586) 
(list 1600.135 867.7689) 
(list 1600.135 867.7792) 
(list 1600.135 867.7894) 
(list 1600.135 867.7997) 
(list 1600.135 867.81) 
(list 1600 867.81)))
(apply 'command (append '("pline") coords '("c")))
(setq tap5 (ssadd (entlast) tap5))
(command "_mirror" (entlast) "" "1600,900" "1600,901" "No")
(setq tap5 (ssadd (entlast) tap5))
(setq coords (list 
(list 1600.4396 867.44) 
(list 1600.4314 867.44) 
(list 1600.4314 867.4503) 
(list 1600.4308 867.4606) 
(list 1600.4298 867.4708) 
(list 1600.4283 867.4811) 
(list 1600.4263 867.4914) 
(list 1600.424 867.5017) 
(list 1600.4213 867.5119) 
(list 1600.4183 867.5222) 
(list 1600.4152 867.5325) 
(list 1600.4119 867.5428) 
(list 1600.4087 867.5531) 
(list 1600.4057 867.5633) 
(list 1600.4028 867.5736) 
(list 1600.4003 867.5839) 
(list 1600.3981 867.5942) 
(list 1600.3965 867.6044) 
(list 1600.3954 867.6147) 
(list 1600.3948 867.625) 
(list 1600.3949 867.6353) 
(list 1600.3956 867.6456) 
(list 1600.397 867.6558) 
(list 1600.3989 867.6661) 
(list 1600.4014 867.6764) 
(list 1600.4043 867.6867) 
(list 1600.4077 867.6969) 
(list 1600.4113 867.7072) 
(list 1600.4152 867.7175) 
(list 1600.4191 867.7278) 
(list 1600.423 867.7381) 
(list 1600.4267 867.7483) 
(list 1600.4301 867.7586) 
(list 1600.4332 867.7689) 
(list 1600.4357 867.7792) 
(list 1600.4377 867.7894) 
(list 1600.439 867.7997) 
(list 1600.4396 867.81) 
(list 1600.4396 867.81)))
(apply 'command (append '("pline") coords '("c")))
(setq tap5 (ssadd (entlast) tap5))
(command "_mirror" (entlast) "" "1600,900" "1600,901" "No")
(setq tap5 (ssadd (entlast) tap5))
(setq coords (list 
(list 1601.076 867.44) 
(list 1600.4396 867.44) 
(list 1600.4396 867.4503) 
(list 1600.4396 867.4606) 
(list 1600.4396 867.4708) 
(list 1600.4396 867.4811) 
(list 1600.4396 867.4914) 
(list 1600.4396 867.5017) 
(list 1600.4396 867.5119) 
(list 1600.4396 867.5222) 
(list 1600.4396 867.5325) 
(list 1600.4396 867.5428) 
(list 1600.4396 867.5531) 
(list 1600.4396 867.5633) 
(list 1600.4396 867.5736) 
(list 1600.4396 867.5839) 
(list 1600.4396 867.5942) 
(list 1600.4396 867.6044) 
(list 1600.4396 867.6147) 
(list 1600.4396 867.625) 
(list 1600.4396 867.6353) 
(list 1600.4396 867.6456) 
(list 1600.4396 867.6558) 
(list 1600.4396 867.6661) 
(list 1600.4396 867.6764) 
(list 1600.4396 867.6867) 
(list 1600.4396 867.6969) 
(list 1600.4396 867.7072) 
(list 1600.4396 867.7175) 
(list 1600.4396 867.7278) 
(list 1600.4396 867.7381) 
(list 1600.4396 867.7483) 
(list 1600.4396 867.7586) 
(list 1600.4396 867.7689) 
(list 1600.4396 867.7792) 
(list 1600.4396 867.7894) 
(list 1600.4396 867.7997) 
(list 1600.4396 867.81) 
(list 1601.076 867.81)))
(apply 'command (append '("pline") coords '("c")))
(setq tap5 (ssadd (entlast) tap5))
(command "_mirror" (entlast) "" "1600,900" "1600,901" "No")
(setq tap5 (ssadd (entlast) tap5))
(setq coords (list 
(list 1600 867.81) 
(list 1600.135 867.81) 
(list 1600.135 867.8203) 
(list 1600.135 867.8306) 
(list 1600.135 867.8408) 
(list 1600.135 867.8511) 
(list 1600.135 867.8614) 
(list 1600.135 867.8717) 
(list 1600.135 867.8819) 
(list 1600.135 867.8922) 
(list 1600.135 867.9025) 
(list 1600.135 867.9128) 
(list 1600.135 867.9231) 
(list 1600.135 867.9333) 
(list 1600.135 867.9436) 
(list 1600.135 867.9539) 
(list 1600.135 867.9642) 
(list 1600.135 867.9744) 
(list 1600.135 867.9847) 
(list 1600.135 867.995) 
(list 1600.135 868.0053) 
(list 1600.135 868.0156) 
(list 1600.135 868.0258) 
(list 1600.135 868.0361) 
(list 1600.135 868.0464) 
(list 1600.135 868.0567) 
(list 1600.135 868.0669) 
(list 1600.135 868.0772) 
(list 1600.135 868.0875) 
(list 1600.135 868.0978) 
(list 1600.135 868.1081) 
(list 1600.135 868.1183) 
(list 1600.135 868.1286) 
(list 1600.135 868.1389) 
(list 1600.135 868.1492) 
(list 1600.135 868.1594) 
(list 1600.135 868.1697) 
(list 1600.135 868.18) 
(list 1600 868.18)))
(apply 'command (append '("pline") coords '("c")))
(setq tap5 (ssadd (entlast) tap5))
(command "_mirror" (entlast) "" "1600,900" "1600,901" "No")
(setq tap5 (ssadd (entlast) tap5))
(setq coords (list 
(list 1600.4478 867.81) 
(list 1600.4396 867.81) 
(list 1600.4395 867.8203) 
(list 1600.4386 867.8306) 
(list 1600.4369 867.8408) 
(list 1600.4346 867.8511) 
(list 1600.4316 867.8614) 
(list 1600.4281 867.8717) 
(list 1600.4241 867.8819) 
(list 1600.4198 867.8922) 
(list 1600.4152 867.9025) 
(list 1600.4106 867.9128) 
(list 1600.406 867.9231) 
(list 1600.4017 867.9333) 
(list 1600.3977 867.9436) 
(list 1600.3941 867.9539) 
(list 1600.3912 867.9642) 
(list 1600.3889 867.9744) 
(list 1600.3874 867.9847) 
(list 1600.3868 867.995) 
(list 1600.387 868.0053) 
(list 1600.3881 868.0156) 
(list 1600.39 868.0258) 
(list 1600.3927 868.0361) 
(list 1600.3962 868.0464) 
(list 1600.4003 868.0567) 
(list 1600.405 868.0669) 
(list 1600.41 868.0772) 
(list 1600.4153 868.0875) 
(list 1600.4206 868.0978) 
(list 1600.4258 868.1081) 
(list 1600.4308 868.1183) 
(list 1600.4354 868.1286) 
(list 1600.4395 868.1389) 
(list 1600.4428 868.1492) 
(list 1600.4454 868.1594) 
(list 1600.4471 868.1697) 
(list 1600.4478 868.18) 
(list 1600.4478 868.18)))
(apply 'command (append '("pline") coords '("c")))
(setq tap5 (ssadd (entlast) tap5))
(command "_mirror" (entlast) "" "1600,900" "1600,901" "No")
(setq tap5 (ssadd (entlast) tap5))
(setq coords (list 
(list 1601.076 867.81) 
(list 1600.4478 867.81) 
(list 1600.4478 867.8203) 
(list 1600.4478 867.8306) 
(list 1600.4478 867.8408) 
(list 1600.4478 867.8511) 
(list 1600.4478 867.8614) 
(list 1600.4478 867.8717) 
(list 1600.4478 867.8819) 
(list 1600.4478 867.8922) 
(list 1600.4478 867.9025) 
(list 1600.4478 867.9128) 
(list 1600.4478 867.9231) 
(list 1600.4478 867.9333) 
(list 1600.4478 867.9436) 
(list 1600.4478 867.9539) 
(list 1600.4478 867.9642) 
(list 1600.4478 867.9744) 
(list 1600.4478 867.9847) 
(list 1600.4478 867.995) 
(list 1600.4478 868.0053) 
(list 1600.4478 868.0156) 
(list 1600.4478 868.0258) 
(list 1600.4478 868.0361) 
(list 1600.4478 868.0464) 
(list 1600.4478 868.0567) 
(list 1600.4478 868.0669) 
(list 1600.4478 868.0772) 
(list 1600.4478 868.0875) 
(list 1600.4478 868.0978) 
(list 1600.4478 868.1081) 
(list 1600.4478 868.1183) 
(list 1600.4478 868.1286) 
(list 1600.4478 868.1389) 
(list 1600.4478 868.1492) 
(list 1600.4478 868.1594) 
(list 1600.4478 868.1697) 
(list 1600.4478 868.18) 
(list 1601.076 868.18)))
(apply 'command (append '("pline") coords '("c")))
(setq tap5 (ssadd (entlast) tap5))
(command "_mirror" (entlast) "" "1600,900" "1600,901" "No")
(setq tap5 (ssadd (entlast) tap5))
(setq coords (list 
(list 1600 868.18) 
(list 1600.135 868.18) 
(list 1600.135 868.1903) 
(list 1600.135 868.2006) 
(list 1600.135 868.2108) 
(list 1600.135 868.2211) 
(list 1600.135 868.2314) 
(list 1600.135 868.2417) 
(list 1600.135 868.2519) 
(list 1600.135 868.2622) 
(list 1600.135 868.2725) 
(list 1600.135 868.2828) 
(list 1600.135 868.2931) 
(list 1600.135 868.3033) 
(list 1600.135 868.3136) 
(list 1600.135 868.3239) 
(list 1600.135 868.3342) 
(list 1600.135 868.3444) 
(list 1600.135 868.3547) 
(list 1600.135 868.365) 
(list 1600.135 868.3753) 
(list 1600.135 868.3856) 
(list 1600.135 868.3958) 
(list 1600.135 868.4061) 
(list 1600.135 868.4164) 
(list 1600.135 868.4267) 
(list 1600.135 868.4369) 
(list 1600.135 868.4472) 
(list 1600.135 868.4575) 
(list 1600.135 868.4678) 
(list 1600.135 868.4781) 
(list 1600.135 868.4883) 
(list 1600.135 868.4986) 
(list 1600.135 868.5089) 
(list 1600.135 868.5192) 
(list 1600.135 868.5294) 
(list 1600.135 868.5397) 
(list 1600.135 868.55) 
(list 1600 868.55)))
(apply 'command (append '("pline") coords '("c")))
(setq tap5 (ssadd (entlast) tap5))
(command "_mirror" (entlast) "" "1600,900" "1600,901" "No")
(setq tap5 (ssadd (entlast) tap5))
(setq coords (list 
(list 1600.456 868.18) 
(list 1600.4478 868.18) 
(list 1600.4475 868.1903) 
(list 1600.4463 868.2006) 
(list 1600.444 868.2108) 
(list 1600.4409 868.2211) 
(list 1600.4369 868.2314) 
(list 1600.4322 868.2417) 
(list 1600.4269 868.2519) 
(list 1600.4212 868.2622) 
(list 1600.4153 868.2725) 
(list 1600.4092 868.2828) 
(list 1600.4033 868.2931) 
(list 1600.3977 868.3033) 
(list 1600.3925 868.3136) 
(list 1600.3879 868.3239) 
(list 1600.3842 868.3342) 
(list 1600.3813 868.3444) 
(list 1600.3795 868.3547) 
(list 1600.3787 868.365) 
(list 1600.379 868.3753) 
(list 1600.3805 868.3856) 
(list 1600.383 868.3958) 
(list 1600.3866 868.4061) 
(list 1600.3911 868.4164) 
(list 1600.3963 868.4267) 
(list 1600.4023 868.4369) 
(list 1600.4086 868.4472) 
(list 1600.4153 868.4575) 
(list 1600.4221 868.4678) 
(list 1600.4287 868.4781) 
(list 1600.435 868.4883) 
(list 1600.4407 868.4986) 
(list 1600.4458 868.5089) 
(list 1600.45 868.5192) 
(list 1600.4531 868.5294) 
(list 1600.4552 868.5397) 
(list 1600.456 868.55) 
(list 1600.456 868.55)))
(apply 'command (append '("pline") coords '("c")))
(setq tap5 (ssadd (entlast) tap5))
(command "_mirror" (entlast) "" "1600,900" "1600,901" "No")
(setq tap5 (ssadd (entlast) tap5))
(setq coords (list 
(list 1601.076 868.18) 
(list 1600.456 868.18) 
(list 1600.456 868.1903) 
(list 1600.456 868.2006) 
(list 1600.456 868.2108) 
(list 1600.456 868.2211) 
(list 1600.456 868.2314) 
(list 1600.456 868.2417) 
(list 1600.456 868.2519) 
(list 1600.456 868.2622) 
(list 1600.456 868.2725) 
(list 1600.456 868.2828) 
(list 1600.456 868.2931) 
(list 1600.456 868.3033) 
(list 1600.456 868.3136) 
(list 1600.456 868.3239) 
(list 1600.456 868.3342) 
(list 1600.456 868.3444) 
(list 1600.456 868.3547) 
(list 1600.456 868.365) 
(list 1600.456 868.3753) 
(list 1600.456 868.3856) 
(list 1600.456 868.3958) 
(list 1600.456 868.4061) 
(list 1600.456 868.4164) 
(list 1600.456 868.4267) 
(list 1600.456 868.4369) 
(list 1600.456 868.4472) 
(list 1600.456 868.4575) 
(list 1600.456 868.4678) 
(list 1600.456 868.4781) 
(list 1600.456 868.4883) 
(list 1600.456 868.4986) 
(list 1600.456 868.5089) 
(list 1600.456 868.5192) 
(list 1600.456 868.5294) 
(list 1600.456 868.5397) 
(list 1600.456 868.55) 
(list 1601.076 868.55)))
(apply 'command (append '("pline") coords '("c")))
(setq tap5 (ssadd (entlast) tap5))
(command "_mirror" (entlast) "" "1600,900" "1600,901" "No")
(setq tap5 (ssadd (entlast) tap5))
(setq coords (list 
(list 1600 868.55) 
(list 1600.135 868.55) 
(list 1600.135 868.5603) 
(list 1600.135 868.5706) 
(list 1600.135 868.5808) 
(list 1600.135 868.5911) 
(list 1600.135 868.6014) 
(list 1600.135 868.6117) 
(list 1600.135 868.6219) 
(list 1600.135 868.6322) 
(list 1600.135 868.6425) 
(list 1600.135 868.6528) 
(list 1600.135 868.6631) 
(list 1600.135 868.6733) 
(list 1600.135 868.6836) 
(list 1600.135 868.6939) 
(list 1600.135 868.7042) 
(list 1600.135 868.7144) 
(list 1600.135 868.7247) 
(list 1600.135 868.735) 
(list 1600.135 868.7453) 
(list 1600.135 868.7556) 
(list 1600.135 868.7658) 
(list 1600.135 868.7761) 
(list 1600.135 868.7864) 
(list 1600.135 868.7967) 
(list 1600.135 868.8069) 
(list 1600.135 868.8172) 
(list 1600.135 868.8275) 
(list 1600.135 868.8378) 
(list 1600.135 868.8481) 
(list 1600.135 868.8583) 
(list 1600.135 868.8686) 
(list 1600.135 868.8789) 
(list 1600.135 868.8892) 
(list 1600.135 868.8994) 
(list 1600.135 868.9097) 
(list 1600.135 868.92) 
(list 1600 868.92)))
(apply 'command (append '("pline") coords '("c")))
(setq tap5 (ssadd (entlast) tap5))
(command "_mirror" (entlast) "" "1600,900" "1600,901" "No")
(setq tap5 (ssadd (entlast) tap5))
(setq coords (list 
(list 1600.4642 868.55) 
(list 1600.456 868.55) 
(list 1600.4556 868.5603) 
(list 1600.454 868.5706) 
(list 1600.4511 868.5808) 
(list 1600.4472 868.5911) 
(list 1600.4422 868.6014) 
(list 1600.4364 868.6117) 
(list 1600.4298 868.6219) 
(list 1600.4227 868.6322) 
(list 1600.4153 868.6425) 
(list 1600.4079 868.6528) 
(list 1600.4006 868.6631) 
(list 1600.3937 868.6733) 
(list 1600.3873 868.6836) 
(list 1600.3818 868.6939) 
(list 1600.3772 868.7042) 
(list 1600.3738 868.7144) 
(list 1600.3715 868.7247) 
(list 1600.3706 868.735) 
(list 1600.3711 868.7453) 
(list 1600.3729 868.7556) 
(list 1600.376 868.7658) 
(list 1600.3804 868.7761) 
(list 1600.3859 868.7864) 
(list 1600.3923 868.7967) 
(list 1600.3995 868.8069) 
(list 1600.4073 868.8172) 
(list 1600.4154 868.8275) 
(list 1600.4235 868.8378) 
(list 1600.4315 868.8481) 
(list 1600.4391 868.8583) 
(list 1600.446 868.8686) 
(list 1600.4521 868.8789) 
(list 1600.4571 868.8892) 
(list 1600.4608 868.8994) 
(list 1600.4632 868.9097) 
(list 1600.4642 868.92) 
(list 1600.4642 868.92)))
(apply 'command (append '("pline") coords '("c")))
(setq tap5 (ssadd (entlast) tap5))
(command "_mirror" (entlast) "" "1600,900" "1600,901" "No")
(setq tap5 (ssadd (entlast) tap5))
(setq coords (list 
(list 1601.076 868.55) 
(list 1600.4642 868.55) 
(list 1600.4642 868.5603) 
(list 1600.4642 868.5706) 
(list 1600.4642 868.5808) 
(list 1600.4642 868.5911) 
(list 1600.4642 868.6014) 
(list 1600.4642 868.6117) 
(list 1600.4642 868.6219) 
(list 1600.4642 868.6322) 
(list 1600.4642 868.6425) 
(list 1600.4642 868.6528) 
(list 1600.4642 868.6631) 
(list 1600.4642 868.6733) 
(list 1600.4642 868.6836) 
(list 1600.4642 868.6939) 
(list 1600.4642 868.7042) 
(list 1600.4642 868.7144) 
(list 1600.4642 868.7247) 
(list 1600.4642 868.735) 
(list 1600.4642 868.7453) 
(list 1600.4642 868.7556) 
(list 1600.4642 868.7658) 
(list 1600.4642 868.7761) 
(list 1600.4642 868.7864) 
(list 1600.4642 868.7967) 
(list 1600.4642 868.8069) 
(list 1600.4642 868.8172) 
(list 1600.4642 868.8275) 
(list 1600.4642 868.8378) 
(list 1600.4642 868.8481) 
(list 1600.4642 868.8583) 
(list 1600.4642 868.8686) 
(list 1600.4642 868.8789) 
(list 1600.4642 868.8892) 
(list 1600.4642 868.8994) 
(list 1600.4642 868.9097) 
(list 1600.4642 868.92) 
(list 1601.076 868.92)))
(apply 'command (append '("pline") coords '("c")))
(setq tap5 (ssadd (entlast) tap5))
(command "_mirror" (entlast) "" "1600,900" "1600,901" "No")
(setq tap5 (ssadd (entlast) tap5))
(setq coords (list 
(list 1600 868.92) 
(list 1600.135 868.92) 
(list 1600.135 868.9303) 
(list 1600.135 868.9406) 
(list 1600.135 868.9508) 
(list 1600.135 868.9611) 
(list 1600.135 868.9714) 
(list 1600.135 868.9817) 
(list 1600.135 868.9919) 
(list 1600.135 869.0022) 
(list 1600.135 869.0125) 
(list 1600.135 869.0228) 
(list 1600.135 869.0331) 
(list 1600.135 869.0433) 
(list 1600.135 869.0536) 
(list 1600.135 869.0639) 
(list 1600.135 869.0742) 
(list 1600.135 869.0844) 
(list 1600.135 869.0947) 
(list 1600.135 869.105) 
(list 1600.135 869.1153) 
(list 1600.135 869.1256) 
(list 1600.135 869.1358) 
(list 1600.135 869.1461) 
(list 1600.135 869.1564) 
(list 1600.135 869.1667) 
(list 1600.135 869.1769) 
(list 1600.135 869.1872) 
(list 1600.135 869.1975) 
(list 1600.135 869.2078) 
(list 1600.135 869.2181) 
(list 1600.135 869.2283) 
(list 1600.135 869.2386) 
(list 1600.135 869.2489) 
(list 1600.135 869.2592) 
(list 1600.135 869.2694) 
(list 1600.135 869.2797) 
(list 1600.135 869.29) 
(list 1600 869.29)))
(apply 'command (append '("pline") coords '("c")))
(setq tap5 (ssadd (entlast) tap5))
(command "_mirror" (entlast) "" "1600,900" "1600,901" "No")
(setq tap5 (ssadd (entlast) tap5))
(setq coords (list 
(list 1600.4724 868.92) 
(list 1600.4642 868.92) 
(list 1600.4637 868.9303) 
(list 1600.4617 868.9406) 
(list 1600.4583 868.9508) 
(list 1600.4535 868.9611) 
(list 1600.4475 868.9714) 
(list 1600.4405 868.9817) 
(list 1600.4326 868.9919) 
(list 1600.4242 869.0022) 
(list 1600.4154 869.0125) 
(list 1600.4066 869.0228) 
(list 1600.3979 869.0331) 
(list 1600.3897 869.0433) 
(list 1600.3822 869.0536) 
(list 1600.3756 869.0639) 
(list 1600.3702 869.0742) 
(list 1600.3662 869.0844) 
(list 1600.3636 869.0947) 
(list 1600.3626 869.105) 
(list 1600.3631 869.1153) 
(list 1600.3653 869.1256) 
(list 1600.3691 869.1358) 
(list 1600.3743 869.1461) 
(list 1600.3807 869.1564) 
(list 1600.3883 869.1667) 
(list 1600.3968 869.1769) 
(list 1600.406 869.1872) 
(list 1600.4154 869.1975) 
(list 1600.425 869.2078) 
(list 1600.4344 869.2181) 
(list 1600.4432 869.2283) 
(list 1600.4513 869.2386) 
(list 1600.4584 869.2489) 
(list 1600.4642 869.2592) 
(list 1600.4685 869.2694) 
(list 1600.4713 869.2797) 
(list 1600.4724 869.29) 
(list 1600.4724 869.29)))
(apply 'command (append '("pline") coords '("c")))
(setq tap5 (ssadd (entlast) tap5))
(command "_mirror" (entlast) "" "1600,900" "1600,901" "No")
(setq tap5 (ssadd (entlast) tap5))
(setq coords (list 
(list 1601.076 868.92) 
(list 1600.4724 868.92) 
(list 1600.4724 868.9303) 
(list 1600.4724 868.9406) 
(list 1600.4724 868.9508) 
(list 1600.4724 868.9611) 
(list 1600.4724 868.9714) 
(list 1600.4724 868.9817) 
(list 1600.4724 868.9919) 
(list 1600.4724 869.0022) 
(list 1600.4724 869.0125) 
(list 1600.4724 869.0228) 
(list 1600.4724 869.0331) 
(list 1600.4724 869.0433) 
(list 1600.4724 869.0536) 
(list 1600.4724 869.0639) 
(list 1600.4724 869.0742) 
(list 1600.4724 869.0844) 
(list 1600.4724 869.0947) 
(list 1600.4724 869.105) 
(list 1600.4724 869.1153) 
(list 1600.4724 869.1256) 
(list 1600.4724 869.1358) 
(list 1600.4724 869.1461) 
(list 1600.4724 869.1564) 
(list 1600.4724 869.1667) 
(list 1600.4724 869.1769) 
(list 1600.4724 869.1872) 
(list 1600.4724 869.1975) 
(list 1600.4724 869.2078) 
(list 1600.4724 869.2181) 
(list 1600.4724 869.2283) 
(list 1600.4724 869.2386) 
(list 1600.4724 869.2489) 
(list 1600.4724 869.2592) 
(list 1600.4724 869.2694) 
(list 1600.4724 869.2797) 
(list 1600.4724 869.29) 
(list 1601.076 869.29)))
(apply 'command (append '("pline") coords '("c")))
(setq tap5 (ssadd (entlast) tap5))
(command "_mirror" (entlast) "" "1600,900" "1600,901" "No")
(setq tap5 (ssadd (entlast) tap5))
(setq coords (list 
(list 1600 869.29) 
(list 1600.135 869.29) 
(list 1600.135 869.3003) 
(list 1600.135 869.3106) 
(list 1600.135 869.3208) 
(list 1600.135 869.3311) 
(list 1600.135 869.3414) 
(list 1600.135 869.3517) 
(list 1600.135 869.3619) 
(list 1600.135 869.3722) 
(list 1600.135 869.3825) 
(list 1600.135 869.3928) 
(list 1600.135 869.4031) 
(list 1600.135 869.4133) 
(list 1600.135 869.4236) 
(list 1600.135 869.4339) 
(list 1600.135 869.4442) 
(list 1600.135 869.4544) 
(list 1600.135 869.4647) 
(list 1600.135 869.475) 
(list 1600.135 869.4853) 
(list 1600.135 869.4956) 
(list 1600.135 869.5058) 
(list 1600.135 869.5161) 
(list 1600.135 869.5264) 
(list 1600.135 869.5367) 
(list 1600.135 869.5469) 
(list 1600.135 869.5572) 
(list 1600.135 869.5675) 
(list 1600.135 869.5778) 
(list 1600.135 869.5881) 
(list 1600.135 869.5983) 
(list 1600.135 869.6086) 
(list 1600.135 869.6189) 
(list 1600.135 869.6292) 
(list 1600.135 869.6394) 
(list 1600.135 869.6497) 
(list 1600.135 869.66) 
(list 1600 869.66)))
(apply 'command (append '("pline") coords '("c")))
(setq tap5 (ssadd (entlast) tap5))
(command "_mirror" (entlast) "" "1600,900" "1600,901" "No")
(setq tap5 (ssadd (entlast) tap5))
(setq coords (list 
(list 1600.4806 869.29) 
(list 1600.4724 869.29) 
(list 1600.4718 869.3003) 
(list 1600.4694 869.3106) 
(list 1600.4654 869.3208) 
(list 1600.4598 869.3311) 
(list 1600.4528 869.3414) 
(list 1600.4446 869.3517) 
(list 1600.4355 869.3619) 
(list 1600.4257 869.3722) 
(list 1600.4155 869.3825) 
(list 1600.4052 869.3928) 
(list 1600.3952 869.4031) 
(list 1600.3857 869.4133) 
(list 1600.377 869.4236) 
(list 1600.3695 869.4339) 
(list 1600.3633 869.4442) 
(list 1600.3586 869.4544) 
(list 1600.3556 869.4647) 
(list 1600.3545 869.475) 
(list 1600.3552 869.4853) 
(list 1600.3578 869.4956) 
(list 1600.3621 869.5058) 
(list 1600.3681 869.5161) 
(list 1600.3756 869.5264) 
(list 1600.3843 869.5367) 
(list 1600.3941 869.5469) 
(list 1600.4046 869.5572) 
(list 1600.4155 869.5675) 
(list 1600.4265 869.5778) 
(list 1600.4372 869.5881) 
(list 1600.4474 869.5983) 
(list 1600.4566 869.6086) 
(list 1600.4647 869.6189) 
(list 1600.4713 869.6292) 
(list 1600.4762 869.6394) 
(list 1600.4794 869.6497) 
(list 1600.4806 869.66) 
(list 1600.4806 869.66)))
(apply 'command (append '("pline") coords '("c")))
(setq tap5 (ssadd (entlast) tap5))
(command "_mirror" (entlast) "" "1600,900" "1600,901" "No")
(setq tap5 (ssadd (entlast) tap5))
(setq coords (list 
(list 1601.076 869.29) 
(list 1600.4806 869.29) 
(list 1600.4806 869.3003) 
(list 1600.4806 869.3106) 
(list 1600.4806 869.3208) 
(list 1600.4806 869.3311) 
(list 1600.4806 869.3414) 
(list 1600.4806 869.3517) 
(list 1600.4806 869.3619) 
(list 1600.4806 869.3722) 
(list 1600.4806 869.3825) 
(list 1600.4806 869.3928) 
(list 1600.4806 869.4031) 
(list 1600.4806 869.4133) 
(list 1600.4806 869.4236) 
(list 1600.4806 869.4339) 
(list 1600.4806 869.4442) 
(list 1600.4806 869.4544) 
(list 1600.4806 869.4647) 
(list 1600.4806 869.475) 
(list 1600.4806 869.4853) 
(list 1600.4806 869.4956) 
(list 1600.4806 869.5058) 
(list 1600.4806 869.5161) 
(list 1600.4806 869.5264) 
(list 1600.4806 869.5367) 
(list 1600.4806 869.5469) 
(list 1600.4806 869.5572) 
(list 1600.4806 869.5675) 
(list 1600.4806 869.5778) 
(list 1600.4806 869.5881) 
(list 1600.4806 869.5983) 
(list 1600.4806 869.6086) 
(list 1600.4806 869.6189) 
(list 1600.4806 869.6292) 
(list 1600.4806 869.6394) 
(list 1600.4806 869.6497) 
(list 1600.4806 869.66) 
(list 1601.076 869.66)))
(apply 'command (append '("pline") coords '("c")))
(setq tap5 (ssadd (entlast) tap5))
(command "_mirror" (entlast) "" "1600,900" "1600,901" "No")
(setq tap5 (ssadd (entlast) tap5))
(setq coords (list 
(list 1600 869.66) 
(list 1600.135 869.66) 
(list 1600.135 869.6703) 
(list 1600.135 869.6806) 
(list 1600.135 869.6908) 
(list 1600.135 869.7011) 
(list 1600.135 869.7114) 
(list 1600.135 869.7217) 
(list 1600.135 869.7319) 
(list 1600.135 869.7422) 
(list 1600.135 869.7525) 
(list 1600.135 869.7628) 
(list 1600.135 869.7731) 
(list 1600.135 869.7833) 
(list 1600.135 869.7936) 
(list 1600.135 869.8039) 
(list 1600.135 869.8142) 
(list 1600.135 869.8244) 
(list 1600.135 869.8347) 
(list 1600.135 869.845) 
(list 1600.135 869.8553) 
(list 1600.135 869.8656) 
(list 1600.135 869.8758) 
(list 1600.135 869.8861) 
(list 1600.135 869.8964) 
(list 1600.135 869.9067) 
(list 1600.135 869.9169) 
(list 1600.135 869.9272) 
(list 1600.135 869.9375) 
(list 1600.135 869.9478) 
(list 1600.135 869.9581) 
(list 1600.135 869.9683) 
(list 1600.135 869.9786) 
(list 1600.135 869.9889) 
(list 1600.135 869.9992) 
(list 1600.135 870.0094) 
(list 1600.135 870.0197) 
(list 1600.135 870.03) 
(list 1600 870.03)))
(apply 'command (append '("pline") coords '("c")))
(setq tap5 (ssadd (entlast) tap5))
(command "_mirror" (entlast) "" "1600,900" "1600,901" "No")
(setq tap5 (ssadd (entlast) tap5))
(setq coords (list 
(list 1600.4888 869.66) 
(list 1600.4806 869.66) 
(list 1600.4798 869.6703) 
(list 1600.4771 869.6806) 
(list 1600.4725 869.6908) 
(list 1600.4661 869.7011) 
(list 1600.4581 869.7114) 
(list 1600.4488 869.7217) 
(list 1600.4383 869.7319) 
(list 1600.4272 869.7422) 
(list 1600.4155 869.7525) 
(list 1600.4039 869.7628) 
(list 1600.3925 869.7731) 
(list 1600.3817 869.7833) 
(list 1600.3718 869.7936) 
(list 1600.3633 869.8039) 
(list 1600.3563 869.8142) 
(list 1600.351 869.8244) 
(list 1600.3477 869.8347) 
(list 1600.3464 869.845) 
(list 1600.3473 869.8553) 
(list 1600.3502 869.8656) 
(list 1600.3551 869.8758) 
(list 1600.3619 869.8861) 
(list 1600.3704 869.8964) 
(list 1600.3803 869.9067) 
(list 1600.3914 869.9169) 
(list 1600.4033 869.9272) 
(list 1600.4156 869.9375) 
(list 1600.428 869.9478) 
(list 1600.4401 869.9581) 
(list 1600.4515 869.9683) 
(list 1600.4619 869.9786) 
(list 1600.471 869.9889) 
(list 1600.4784 869.9992) 
(list 1600.484 870.0094) 
(list 1600.4875 870.0197) 
(list 1600.4888 870.03) 
(list 1600.4888 870.03)))
(apply 'command (append '("pline") coords '("c")))
(setq tap5 (ssadd (entlast) tap5))
(command "_mirror" (entlast) "" "1600,900" "1600,901" "No")
(setq tap5 (ssadd (entlast) tap5))
(setq coords (list 
(list 1601.076 869.66) 
(list 1600.4888 869.66) 
(list 1600.4888 869.6703) 
(list 1600.4888 869.6806) 
(list 1600.4888 869.6908) 
(list 1600.4888 869.7011) 
(list 1600.4888 869.7114) 
(list 1600.4888 869.7217) 
(list 1600.4888 869.7319) 
(list 1600.4888 869.7422) 
(list 1600.4888 869.7525) 
(list 1600.4888 869.7628) 
(list 1600.4888 869.7731) 
(list 1600.4888 869.7833) 
(list 1600.4888 869.7936) 
(list 1600.4888 869.8039) 
(list 1600.4888 869.8142) 
(list 1600.4888 869.8244) 
(list 1600.4888 869.8347) 
(list 1600.4888 869.845) 
(list 1600.4888 869.8553) 
(list 1600.4888 869.8656) 
(list 1600.4888 869.8758) 
(list 1600.4888 869.8861) 
(list 1600.4888 869.8964) 
(list 1600.4888 869.9067) 
(list 1600.4888 869.9169) 
(list 1600.4888 869.9272) 
(list 1600.4888 869.9375) 
(list 1600.4888 869.9478) 
(list 1600.4888 869.9581) 
(list 1600.4888 869.9683) 
(list 1600.4888 869.9786) 
(list 1600.4888 869.9889) 
(list 1600.4888 869.9992) 
(list 1600.4888 870.0094) 
(list 1600.4888 870.0197) 
(list 1600.4888 870.03) 
(list 1601.076 870.03)))
(apply 'command (append '("pline") coords '("c")))
(setq tap5 (ssadd (entlast) tap5))
(command "_mirror" (entlast) "" "1600,900" "1600,901" "No")
(setq tap5 (ssadd (entlast) tap5))
(setq coords (list 
(list 1600 870.03) 
(list 1600.135 870.03) 
(list 1600.135 870.0403) 
(list 1600.135 870.0506) 
(list 1600.135 870.0608) 
(list 1600.135 870.0711) 
(list 1600.135 870.0814) 
(list 1600.135 870.0917) 
(list 1600.135 870.1019) 
(list 1600.135 870.1122) 
(list 1600.135 870.1225) 
(list 1600.135 870.1328) 
(list 1600.135 870.1431) 
(list 1600.135 870.1533) 
(list 1600.135 870.1636) 
(list 1600.135 870.1739) 
(list 1600.135 870.1842) 
(list 1600.135 870.1944) 
(list 1600.135 870.2047) 
(list 1600.135 870.215) 
(list 1600.135 870.2253) 
(list 1600.135 870.2356) 
(list 1600.135 870.2458) 
(list 1600.135 870.2561) 
(list 1600.135 870.2664) 
(list 1600.135 870.2767) 
(list 1600.135 870.2869) 
(list 1600.135 870.2972) 
(list 1600.135 870.3075) 
(list 1600.135 870.3178) 
(list 1600.135 870.3281) 
(list 1600.135 870.3383) 
(list 1600.135 870.3486) 
(list 1600.135 870.3589) 
(list 1600.135 870.3692) 
(list 1600.135 870.3794) 
(list 1600.135 870.3897) 
(list 1600.135 870.4) 
(list 1600 870.4)))
(apply 'command (append '("pline") coords '("c")))
(setq tap5 (ssadd (entlast) tap5))
(command "_mirror" (entlast) "" "1600,900" "1600,901" "No")
(setq tap5 (ssadd (entlast) tap5))
(setq coords (list 
(list 1600.497 870.03) 
(list 1600.4888 870.03) 
(list 1600.4879 870.0403) 
(list 1600.4848 870.0506) 
(list 1600.4796 870.0608) 
(list 1600.4724 870.0711) 
(list 1600.4634 870.0814) 
(list 1600.4529 870.0917) 
(list 1600.4412 870.1019) 
(list 1600.4286 870.1122) 
(list 1600.4156 870.1225) 
(list 1600.4025 870.1328) 
(list 1600.3897 870.1431) 
(list 1600.3777 870.1533) 
(list 1600.3667 870.1636) 
(list 1600.3571 870.1739) 
(list 1600.3493 870.1842) 
(list 1600.3434 870.1944) 
(list 1600.3398 870.2047) 
(list 1600.3384 870.215) 
(list 1600.3393 870.2253) 
(list 1600.3426 870.2356) 
(list 1600.3481 870.2458) 
(list 1600.3558 870.2561) 
(list 1600.3653 870.2664) 
(list 1600.3763 870.2767) 
(list 1600.3887 870.2869) 
(list 1600.4019 870.2972) 
(list 1600.4156 870.3075) 
(list 1600.4295 870.3178) 
(list 1600.4429 870.3281) 
(list 1600.4556 870.3383) 
(list 1600.4672 870.3486) 
(list 1600.4773 870.3589) 
(list 1600.4855 870.3692) 
(list 1600.4917 870.3794) 
(list 1600.4955 870.3897) 
(list 1600.497 870.4) 
(list 1600.497 870.4)))
(apply 'command (append '("pline") coords '("c")))
(setq tap5 (ssadd (entlast) tap5))
(command "_mirror" (entlast) "" "1600,900" "1600,901" "No")
(setq tap5 (ssadd (entlast) tap5))
(setq coords (list 
(list 1601.076 870.03) 
(list 1600.497 870.03) 
(list 1600.497 870.0403) 
(list 1600.497 870.0506) 
(list 1600.497 870.0608) 
(list 1600.497 870.0711) 
(list 1600.497 870.0814) 
(list 1600.497 870.0917) 
(list 1600.497 870.1019) 
(list 1600.497 870.1122) 
(list 1600.497 870.1225) 
(list 1600.497 870.1328) 
(list 1600.497 870.1431) 
(list 1600.497 870.1533) 
(list 1600.497 870.1636) 
(list 1600.497 870.1739) 
(list 1600.497 870.1842) 
(list 1600.497 870.1944) 
(list 1600.497 870.2047) 
(list 1600.497 870.215) 
(list 1600.497 870.2253) 
(list 1600.497 870.2356) 
(list 1600.497 870.2458) 
(list 1600.497 870.2561) 
(list 1600.497 870.2664) 
(list 1600.497 870.2767) 
(list 1600.497 870.2869) 
(list 1600.497 870.2972) 
(list 1600.497 870.3075) 
(list 1600.497 870.3178) 
(list 1600.497 870.3281) 
(list 1600.497 870.3383) 
(list 1600.497 870.3486) 
(list 1600.497 870.3589) 
(list 1600.497 870.3692) 
(list 1600.497 870.3794) 
(list 1600.497 870.3897) 
(list 1600.497 870.4) 
(list 1601.076 870.4)))
(apply 'command (append '("pline") coords '("c")))
(setq tap5 (ssadd (entlast) tap5))
(command "_mirror" (entlast) "" "1600,900" "1600,901" "No")
(setq tap5 (ssadd (entlast) tap5))
(setq coords (list 
(list 1600 870.4) 
(list 1600.135 870.4) 
(list 1600.135 870.4103) 
(list 1600.135 870.4206) 
(list 1600.135 870.4308) 
(list 1600.135 870.4411) 
(list 1600.135 870.4514) 
(list 1600.135 870.4617) 
(list 1600.135 870.4719) 
(list 1600.135 870.4822) 
(list 1600.135 870.4925) 
(list 1600.135 870.5028) 
(list 1600.135 870.5131) 
(list 1600.135 870.5233) 
(list 1600.135 870.5336) 
(list 1600.135 870.5439) 
(list 1600.135 870.5542) 
(list 1600.135 870.5644) 
(list 1600.135 870.5747) 
(list 1600.135 870.585) 
(list 1600.135 870.5953) 
(list 1600.135 870.6056) 
(list 1600.135 870.6158) 
(list 1600.135 870.6261) 
(list 1600.135 870.6364) 
(list 1600.135 870.6467) 
(list 1600.135 870.6569) 
(list 1600.135 870.6672) 
(list 1600.135 870.6775) 
(list 1600.135 870.6878) 
(list 1600.135 870.6981) 
(list 1600.135 870.7083) 
(list 1600.135 870.7186) 
(list 1600.135 870.7289) 
(list 1600.135 870.7392) 
(list 1600.135 870.7494) 
(list 1600.135 870.7597) 
(list 1600.135 870.77) 
(list 1600 870.77)))
(apply 'command (append '("pline") coords '("c")))
(setq tap5 (ssadd (entlast) tap5))
(command "_mirror" (entlast) "" "1600,900" "1600,901" "No")
(setq tap5 (ssadd (entlast) tap5))
(setq coords (list 
(list 1600.5052 870.4) 
(list 1600.497 870.4) 
(list 1600.496 870.4103) 
(list 1600.4925 870.4206) 
(list 1600.4867 870.4308) 
(list 1600.4787 870.4411) 
(list 1600.4687 870.4514) 
(list 1600.457 870.4617) 
(list 1600.444 870.4719) 
(list 1600.4301 870.4822) 
(list 1600.4157 870.4925) 
(list 1600.4012 870.5028) 
(list 1600.387 870.5131) 
(list 1600.3737 870.5233) 
(list 1600.3615 870.5336) 
(list 1600.351 870.5439) 
(list 1600.3423 870.5542) 
(list 1600.3359 870.5644) 
(list 1600.3318 870.5747) 
(list 1600.3303 870.585) 
(list 1600.3314 870.5953) 
(list 1600.335 870.6056) 
(list 1600.3412 870.6158) 
(list 1600.3496 870.6261) 
(list 1600.3601 870.6364) 
(list 1600.3723 870.6467) 
(list 1600.386 870.6569) 
(list 1600.4006 870.6672) 
(list 1600.4157 870.6775) 
(list 1600.4309 870.6878) 
(list 1600.4458 870.6981) 
(list 1600.4598 870.7083) 
(list 1600.4725 870.7186) 
(list 1600.4836 870.7289) 
(list 1600.4926 870.7392) 
(list 1600.4994 870.7494) 
(list 1600.5036 870.7597) 
(list 1600.5052 870.77) 
(list 1600.5052 870.77)))
(apply 'command (append '("pline") coords '("c")))
(setq tap5 (ssadd (entlast) tap5))
(command "_mirror" (entlast) "" "1600,900" "1600,901" "No")
(setq tap5 (ssadd (entlast) tap5))
(setq coords (list 
(list 1601.076 870.4) 
(list 1600.5052 870.4) 
(list 1600.5052 870.4103) 
(list 1600.5052 870.4206) 
(list 1600.5052 870.4308) 
(list 1600.5052 870.4411) 
(list 1600.5052 870.4514) 
(list 1600.5052 870.4617) 
(list 1600.5052 870.4719) 
(list 1600.5052 870.4822) 
(list 1600.5052 870.4925) 
(list 1600.5052 870.5028) 
(list 1600.5052 870.5131) 
(list 1600.5052 870.5233) 
(list 1600.5052 870.5336) 
(list 1600.5052 870.5439) 
(list 1600.5052 870.5542) 
(list 1600.5052 870.5644) 
(list 1600.5052 870.5747) 
(list 1600.5052 870.585) 
(list 1600.5052 870.5953) 
(list 1600.5052 870.6056) 
(list 1600.5052 870.6158) 
(list 1600.5052 870.6261) 
(list 1600.5052 870.6364) 
(list 1600.5052 870.6467) 
(list 1600.5052 870.6569) 
(list 1600.5052 870.6672) 
(list 1600.5052 870.6775) 
(list 1600.5052 870.6878) 
(list 1600.5052 870.6981) 
(list 1600.5052 870.7083) 
(list 1600.5052 870.7186) 
(list 1600.5052 870.7289) 
(list 1600.5052 870.7392) 
(list 1600.5052 870.7494) 
(list 1600.5052 870.7597) 
(list 1600.5052 870.77) 
(list 1601.076 870.77)))
(apply 'command (append '("pline") coords '("c")))
(setq tap5 (ssadd (entlast) tap5))
(command "_mirror" (entlast) "" "1600,900" "1600,901" "No")
(setq tap5 (ssadd (entlast) tap5))
(setq coords (list 
(list 1600 870.77) 
(list 1600.135 870.77) 
(list 1600.135 870.7803) 
(list 1600.135 870.7906) 
(list 1600.135 870.8008) 
(list 1600.135 870.8111) 
(list 1600.135 870.8214) 
(list 1600.135 870.8317) 
(list 1600.135 870.8419) 
(list 1600.135 870.8522) 
(list 1600.135 870.8625) 
(list 1600.135 870.8728) 
(list 1600.135 870.8831) 
(list 1600.135 870.8933) 
(list 1600.135 870.9036) 
(list 1600.135 870.9139) 
(list 1600.135 870.9242) 
(list 1600.135 870.9344) 
(list 1600.135 870.9447) 
(list 1600.135 870.955) 
(list 1600.135 870.9653) 
(list 1600.135 870.9756) 
(list 1600.135 870.9858) 
(list 1600.135 870.9961) 
(list 1600.135 871.0064) 
(list 1600.135 871.0167) 
(list 1600.135 871.0269) 
(list 1600.135 871.0372) 
(list 1600.135 871.0475) 
(list 1600.135 871.0578) 
(list 1600.135 871.0681) 
(list 1600.135 871.0783) 
(list 1600.135 871.0886) 
(list 1600.135 871.0989) 
(list 1600.135 871.1092) 
(list 1600.135 871.1194) 
(list 1600.135 871.1297) 
(list 1600.135 871.14) 
(list 1600 871.14)))
(apply 'command (append '("pline") coords '("c")))
(setq tap5 (ssadd (entlast) tap5))
(command "_mirror" (entlast) "" "1600,900" "1600,901" "No")
(setq tap5 (ssadd (entlast) tap5))
(setq coords (list 
(list 1600.5134 870.77) 
(list 1600.5052 870.77) 
(list 1600.5041 870.7803) 
(list 1600.5002 870.7906) 
(list 1600.4938 870.8008) 
(list 1600.485 870.8111) 
(list 1600.474 870.8214) 
(list 1600.4612 870.8317) 
(list 1600.4469 870.8419) 
(list 1600.4316 870.8522) 
(list 1600.4157 870.8625) 
(list 1600.3998 870.8728) 
(list 1600.3843 870.8831) 
(list 1600.3697 870.8933) 
(list 1600.3564 870.9036) 
(list 1600.3448 870.9139) 
(list 1600.3353 870.9242) 
(list 1600.3283 870.9344) 
(list 1600.3239 870.9447) 
(list 1600.3222 870.955) 
(list 1600.3234 870.9653) 
(list 1600.3275 870.9756) 
(list 1600.3342 870.9858) 
(list 1600.3434 870.9961) 
(list 1600.3549 871.0064) 
(list 1600.3683 871.0167) 
(list 1600.3832 871.0269) 
(list 1600.3992 871.0372) 
(list 1600.4158 871.0475) 
(list 1600.4324 871.0578) 
(list 1600.4486 871.0681) 
(list 1600.4639 871.0783) 
(list 1600.4778 871.0886) 
(list 1600.4899 871.0989) 
(list 1600.4997 871.1092) 
(list 1600.5071 871.1194) 
(list 1600.5117 871.1297) 
(list 1600.5134 871.14) 
(list 1600.5134 871.14)))
(apply 'command (append '("pline") coords '("c")))
(setq tap5 (ssadd (entlast) tap5))
(command "_mirror" (entlast) "" "1600,900" "1600,901" "No")
(setq tap5 (ssadd (entlast) tap5))
(setq coords (list 
(list 1601.076 870.77) 
(list 1600.5134 870.77) 
(list 1600.5134 870.7803) 
(list 1600.5134 870.7906) 
(list 1600.5134 870.8008) 
(list 1600.5134 870.8111) 
(list 1600.5134 870.8214) 
(list 1600.5134 870.8317) 
(list 1600.5134 870.8419) 
(list 1600.5134 870.8522) 
(list 1600.5134 870.8625) 
(list 1600.5134 870.8728) 
(list 1600.5134 870.8831) 
(list 1600.5134 870.8933) 
(list 1600.5134 870.9036) 
(list 1600.5134 870.9139) 
(list 1600.5134 870.9242) 
(list 1600.5134 870.9344) 
(list 1600.5134 870.9447) 
(list 1600.5134 870.955) 
(list 1600.5134 870.9653) 
(list 1600.5134 870.9756) 
(list 1600.5134 870.9858) 
(list 1600.5134 870.9961) 
(list 1600.5134 871.0064) 
(list 1600.5134 871.0167) 
(list 1600.5134 871.0269) 
(list 1600.5134 871.0372) 
(list 1600.5134 871.0475) 
(list 1600.5134 871.0578) 
(list 1600.5134 871.0681) 
(list 1600.5134 871.0783) 
(list 1600.5134 871.0886) 
(list 1600.5134 871.0989) 
(list 1600.5134 871.1092) 
(list 1600.5134 871.1194) 
(list 1600.5134 871.1297) 
(list 1600.5134 871.14) 
(list 1601.076 871.14)))
(apply 'command (append '("pline") coords '("c")))
(setq tap5 (ssadd (entlast) tap5))
(command "_mirror" (entlast) "" "1600,900" "1600,901" "No")
(setq tap5 (ssadd (entlast) tap5))
(setq coords (list 
(list 1600 871.14) 
(list 1600.135 871.14) 
(list 1600.135 871.1503) 
(list 1600.135 871.1606) 
(list 1600.135 871.1708) 
(list 1600.135 871.1811) 
(list 1600.135 871.1914) 
(list 1600.135 871.2017) 
(list 1600.135 871.2119) 
(list 1600.135 871.2222) 
(list 1600.135 871.2325) 
(list 1600.135 871.2428) 
(list 1600.135 871.2531) 
(list 1600.135 871.2633) 
(list 1600.135 871.2736) 
(list 1600.135 871.2839) 
(list 1600.135 871.2942) 
(list 1600.135 871.3044) 
(list 1600.135 871.3147) 
(list 1600.135 871.325) 
(list 1600.135 871.3353) 
(list 1600.135 871.3456) 
(list 1600.135 871.3558) 
(list 1600.135 871.3661) 
(list 1600.135 871.3764) 
(list 1600.135 871.3867) 
(list 1600.135 871.3969) 
(list 1600.135 871.4072) 
(list 1600.135 871.4175) 
(list 1600.135 871.4278) 
(list 1600.135 871.4381) 
(list 1600.135 871.4483) 
(list 1600.135 871.4586) 
(list 1600.135 871.4689) 
(list 1600.135 871.4792) 
(list 1600.135 871.4894) 
(list 1600.135 871.4997) 
(list 1600.135 871.51) 
(list 1600 871.51)))
(apply 'command (append '("pline") coords '("c")))
(setq tap5 (ssadd (entlast) tap5))
(command "_mirror" (entlast) "" "1600,900" "1600,901" "No")
(setq tap5 (ssadd (entlast) tap5))
(setq coords (list 
(list 1600.5216 871.14) 
(list 1600.5134 871.14) 
(list 1600.5121 871.1503) 
(list 1600.5079 871.1606) 
(list 1600.5009 871.1708) 
(list 1600.4913 871.1811) 
(list 1600.4793 871.1914) 
(list 1600.4653 871.2017) 
(list 1600.4497 871.2119) 
(list 1600.4331 871.2222) 
(list 1600.4158 871.2325) 
(list 1600.3985 871.2428) 
(list 1600.3816 871.2531) 
(list 1600.3657 871.2633) 
(list 1600.3512 871.2736) 
(list 1600.3386 871.2839) 
(list 1600.3284 871.2942) 
(list 1600.3207 871.3044) 
(list 1600.3159 871.3147) 
(list 1600.3142 871.325) 
(list 1600.3155 871.3353) 
(list 1600.3199 871.3456) 
(list 1600.3272 871.3558) 
(list 1600.3373 871.3661) 
(list 1600.3498 871.3764) 
(list 1600.3643 871.3867) 
(list 1600.3805 871.3969) 
(list 1600.3979 871.4072) 
(list 1600.4159 871.4175) 
(list 1600.4339 871.4278) 
(list 1600.4515 871.4381) 
(list 1600.468 871.4483) 
(list 1600.4831 871.4586) 
(list 1600.4962 871.4689) 
(list 1600.5068 871.4792) 
(list 1600.5148 871.4894) 
(list 1600.5198 871.4997) 
(list 1600.5216 871.51) 
(list 1600.5216 871.51)))
(apply 'command (append '("pline") coords '("c")))
(setq tap5 (ssadd (entlast) tap5))
(command "_mirror" (entlast) "" "1600,900" "1600,901" "No")
(setq tap5 (ssadd (entlast) tap5))
(setq coords (list 
(list 1601.076 871.14) 
(list 1600.5216 871.14) 
(list 1600.5216 871.1503) 
(list 1600.5216 871.1606) 
(list 1600.5216 871.1708) 
(list 1600.5216 871.1811) 
(list 1600.5216 871.1914) 
(list 1600.5216 871.2017) 
(list 1600.5216 871.2119) 
(list 1600.5216 871.2222) 
(list 1600.5216 871.2325) 
(list 1600.5216 871.2428) 
(list 1600.5216 871.2531) 
(list 1600.5216 871.2633) 
(list 1600.5216 871.2736) 
(list 1600.5216 871.2839) 
(list 1600.5216 871.2942) 
(list 1600.5216 871.3044) 
(list 1600.5216 871.3147) 
(list 1600.5216 871.325) 
(list 1600.5216 871.3353) 
(list 1600.5216 871.3456) 
(list 1600.5216 871.3558) 
(list 1600.5216 871.3661) 
(list 1600.5216 871.3764) 
(list 1600.5216 871.3867) 
(list 1600.5216 871.3969) 
(list 1600.5216 871.4072) 
(list 1600.5216 871.4175) 
(list 1600.5216 871.4278) 
(list 1600.5216 871.4381) 
(list 1600.5216 871.4483) 
(list 1600.5216 871.4586) 
(list 1600.5216 871.4689) 
(list 1600.5216 871.4792) 
(list 1600.5216 871.4894) 
(list 1600.5216 871.4997) 
(list 1600.5216 871.51) 
(list 1601.076 871.51)))
(apply 'command (append '("pline") coords '("c")))
(setq tap5 (ssadd (entlast) tap5))
(command "_mirror" (entlast) "" "1600,900" "1600,901" "No")
(setq tap5 (ssadd (entlast) tap5))
(setq coords (list 
(list 1600 871.51) 
(list 1600.135 871.51) 
(list 1600.135 871.5203) 
(list 1600.135 871.5306) 
(list 1600.135 871.5408) 
(list 1600.135 871.5511) 
(list 1600.135 871.5614) 
(list 1600.135 871.5717) 
(list 1600.135 871.5819) 
(list 1600.135 871.5922) 
(list 1600.135 871.6025) 
(list 1600.135 871.6128) 
(list 1600.135 871.6231) 
(list 1600.135 871.6333) 
(list 1600.135 871.6436) 
(list 1600.135 871.6539) 
(list 1600.135 871.6642) 
(list 1600.135 871.6744) 
(list 1600.135 871.6847) 
(list 1600.135 871.695) 
(list 1600.135 871.7053) 
(list 1600.135 871.7156) 
(list 1600.135 871.7258) 
(list 1600.135 871.7361) 
(list 1600.135 871.7464) 
(list 1600.135 871.7567) 
(list 1600.135 871.7669) 
(list 1600.135 871.7772) 
(list 1600.135 871.7875) 
(list 1600.135 871.7978) 
(list 1600.135 871.8081) 
(list 1600.135 871.8183) 
(list 1600.135 871.8286) 
(list 1600.135 871.8389) 
(list 1600.135 871.8492) 
(list 1600.135 871.8594) 
(list 1600.135 871.8697) 
(list 1600.135 871.88) 
(list 1600 871.88)))
(apply 'command (append '("pline") coords '("c")))
(setq tap5 (ssadd (entlast) tap5))
(command "_mirror" (entlast) "" "1600,900" "1600,901" "No")
(setq tap5 (ssadd (entlast) tap5))
(setq coords (list 
(list 1600.5298 871.51) 
(list 1600.5216 871.51) 
(list 1600.5202 871.5203) 
(list 1600.5157 871.5306) 
(list 1600.508 871.5408) 
(list 1600.4976 871.5511) 
(list 1600.4846 871.5614) 
(list 1600.4694 871.5717) 
(list 1600.4526 871.5819) 
(list 1600.4346 871.5922) 
(list 1600.4159 871.6025) 
(list 1600.3971 871.6128) 
(list 1600.3789 871.6231) 
(list 1600.3617 871.6333) 
(list 1600.346 871.6436) 
(list 1600.3325 871.6539) 
(list 1600.3214 871.6642) 
(list 1600.3131 871.6744) 
(list 1600.308 871.6847) 
(list 1600.3061 871.695) 
(list 1600.3075 871.7053) 
(list 1600.3123 871.7156) 
(list 1600.3202 871.7258) 
(list 1600.3311 871.7361) 
(list 1600.3446 871.7464) 
(list 1600.3603 871.7567) 
(list 1600.3778 871.7669) 
(list 1600.3965 871.7772) 
(list 1600.4159 871.7875) 
(list 1600.4354 871.7978) 
(list 1600.4543 871.8081) 
(list 1600.4722 871.8183) 
(list 1600.4884 871.8286) 
(list 1600.5025 871.8389) 
(list 1600.514 871.8492) 
(list 1600.5225 871.8594) 
(list 1600.5278 871.8697) 
(list 1600.5298 871.88) 
(list 1600.5298 871.88)))
(apply 'command (append '("pline") coords '("c")))
(setq tap5 (ssadd (entlast) tap5))
(command "_mirror" (entlast) "" "1600,900" "1600,901" "No")
(setq tap5 (ssadd (entlast) tap5))
(setq coords (list 
(list 1601.076 871.51) 
(list 1600.5298 871.51) 
(list 1600.5298 871.5203) 
(list 1600.5298 871.5306) 
(list 1600.5298 871.5408) 
(list 1600.5298 871.5511) 
(list 1600.5298 871.5614) 
(list 1600.5298 871.5717) 
(list 1600.5298 871.5819) 
(list 1600.5298 871.5922) 
(list 1600.5298 871.6025) 
(list 1600.5298 871.6128) 
(list 1600.5298 871.6231) 
(list 1600.5298 871.6333) 
(list 1600.5298 871.6436) 
(list 1600.5298 871.6539) 
(list 1600.5298 871.6642) 
(list 1600.5298 871.6744) 
(list 1600.5298 871.6847) 
(list 1600.5298 871.695) 
(list 1600.5298 871.7053) 
(list 1600.5298 871.7156) 
(list 1600.5298 871.7258) 
(list 1600.5298 871.7361) 
(list 1600.5298 871.7464) 
(list 1600.5298 871.7567) 
(list 1600.5298 871.7669) 
(list 1600.5298 871.7772) 
(list 1600.5298 871.7875) 
(list 1600.5298 871.7978) 
(list 1600.5298 871.8081) 
(list 1600.5298 871.8183) 
(list 1600.5298 871.8286) 
(list 1600.5298 871.8389) 
(list 1600.5298 871.8492) 
(list 1600.5298 871.8594) 
(list 1600.5298 871.8697) 
(list 1600.5298 871.88) 
(list 1601.076 871.88)))
(apply 'command (append '("pline") coords '("c")))
(setq tap5 (ssadd (entlast) tap5))
(command "_mirror" (entlast) "" "1600,900" "1600,901" "No")
(setq tap5 (ssadd (entlast) tap5))
(setq coords (list 
(list 1600 871.88) 
(list 1600.135 871.88) 
(list 1600.135 871.8903) 
(list 1600.135 871.9006) 
(list 1600.135 871.9108) 
(list 1600.135 871.9211) 
(list 1600.135 871.9314) 
(list 1600.135 871.9417) 
(list 1600.135 871.9519) 
(list 1600.135 871.9622) 
(list 1600.135 871.9725) 
(list 1600.135 871.9828) 
(list 1600.135 871.9931) 
(list 1600.135 872.0033) 
(list 1600.135 872.0136) 
(list 1600.135 872.0239) 
(list 1600.135 872.0342) 
(list 1600.135 872.0444) 
(list 1600.135 872.0547) 
(list 1600.135 872.065) 
(list 1600.135 872.0753) 
(list 1600.135 872.0856) 
(list 1600.135 872.0958) 
(list 1600.135 872.1061) 
(list 1600.135 872.1164) 
(list 1600.135 872.1267) 
(list 1600.135 872.1369) 
(list 1600.135 872.1472) 
(list 1600.135 872.1575) 
(list 1600.135 872.1678) 
(list 1600.135 872.1781) 
(list 1600.135 872.1883) 
(list 1600.135 872.1986) 
(list 1600.135 872.2089) 
(list 1600.135 872.2192) 
(list 1600.135 872.2294) 
(list 1600.135 872.2397) 
(list 1600.135 872.25) 
(list 1600 872.25)))
(apply 'command (append '("pline") coords '("c")))
(setq tap5 (ssadd (entlast) tap5))
(command "_mirror" (entlast) "" "1600,900" "1600,901" "No")
(setq tap5 (ssadd (entlast) tap5))
(setq coords (list 
(list 1600.538 871.88) 
(list 1600.5298 871.88) 
(list 1600.5283 871.8903) 
(list 1600.5234 871.9006) 
(list 1600.5151 871.9108) 
(list 1600.5039 871.9211) 
(list 1600.4899 871.9314) 
(list 1600.4736 871.9417) 
(list 1600.4554 871.9519) 
(list 1600.436 871.9622) 
(list 1600.416 871.9725) 
(list 1600.3958 871.9828) 
(list 1600.3762 871.9931) 
(list 1600.3577 872.0033) 
(list 1600.3409 872.0136) 
(list 1600.3263 872.0239) 
(list 1600.3144 872.0342) 
(list 1600.3056 872.0444) 
(list 1600.3 872.0547) 
(list 1600.298 872.065) 
(list 1600.2996 872.0753) 
(list 1600.3047 872.0856) 
(list 1600.3133 872.0958) 
(list 1600.3249 872.1061) 
(list 1600.3394 872.1164) 
(list 1600.3563 872.1267) 
(list 1600.3751 872.1369) 
(list 1600.3952 872.1472) 
(list 1600.416 872.1575) 
(list 1600.4369 872.1678) 
(list 1600.4572 872.1781) 
(list 1600.4763 872.1883) 
(list 1600.4937 872.1986) 
(list 1600.5088 872.2089) 
(list 1600.5211 872.2192) 
(list 1600.5302 872.2294) 
(list 1600.5359 872.2397) 
(list 1600.538 872.25) 
(list 1600.538 872.25)))
(apply 'command (append '("pline") coords '("c")))
(setq tap5 (ssadd (entlast) tap5))
(command "_mirror" (entlast) "" "1600,900" "1600,901" "No")
(setq tap5 (ssadd (entlast) tap5))
(setq coords (list 
(list 1601.076 871.88) 
(list 1600.538 871.88) 
(list 1600.538 871.8903) 
(list 1600.538 871.9006) 
(list 1600.538 871.9108) 
(list 1600.538 871.9211) 
(list 1600.538 871.9314) 
(list 1600.538 871.9417) 
(list 1600.538 871.9519) 
(list 1600.538 871.9622) 
(list 1600.538 871.9725) 
(list 1600.538 871.9828) 
(list 1600.538 871.9931) 
(list 1600.538 872.0033) 
(list 1600.538 872.0136) 
(list 1600.538 872.0239) 
(list 1600.538 872.0342) 
(list 1600.538 872.0444) 
(list 1600.538 872.0547) 
(list 1600.538 872.065) 
(list 1600.538 872.0753) 
(list 1600.538 872.0856) 
(list 1600.538 872.0958) 
(list 1600.538 872.1061) 
(list 1600.538 872.1164) 
(list 1600.538 872.1267) 
(list 1600.538 872.1369) 
(list 1600.538 872.1472) 
(list 1600.538 872.1575) 
(list 1600.538 872.1678) 
(list 1600.538 872.1781) 
(list 1600.538 872.1883) 
(list 1600.538 872.1986) 
(list 1600.538 872.2089) 
(list 1600.538 872.2192) 
(list 1600.538 872.2294) 
(list 1600.538 872.2397) 
(list 1600.538 872.25) 
(list 1601.076 872.25)))
(apply 'command (append '("pline") coords '("c")))
(setq tap5 (ssadd (entlast) tap5))
(command "_mirror" (entlast) "" "1600,900" "1600,901" "No")
(setq tap5 (ssadd (entlast) tap5))
(command "_block" "blktap5" "1600,900" tap5 "")
(command "_insert" "blktap5" "1600,900" "1" "1" "0")
(command "_insert" "blktap5" "1600,900" "1" "1" "180")
(setq uc5 nil)
(setq uc5 (ssadd))
(setq coords (list 
(list 0 -0.185) 
(list 0.135 -0.185) 
(list 0.135 -0.17472) 
(list 0.135 -0.16444) 
(list 0.135 -0.15417) 
(list 0.135 -0.14389) 
(list 0.135 -0.13361) 
(list 0.135 -0.12333) 
(list 0.135 -0.11306) 
(list 0.135 -0.10278) 
(list 0.135 -0.0925) 
(list 0.135 -0.082222) 
(list 0.135 -0.071944) 
(list 0.135 -0.061667) 
(list 0.135 -0.051389) 
(list 0.135 -0.041111) 
(list 0.135 -0.030833) 
(list 0.135 -0.020556) 
(list 0.135 -0.010278) 
(list 0.135 0) 
(list 0.135 0.010278) 
(list 0.135 0.020556) 
(list 0.135 0.030833) 
(list 0.135 0.041111) 
(list 0.135 0.051389) 
(list 0.135 0.061667) 
(list 0.135 0.071944) 
(list 0.135 0.082222) 
(list 0.135 0.0925) 
(list 0.135 0.10278) 
(list 0.135 0.11306) 
(list 0.135 0.12333) 
(list 0.135 0.13361) 
(list 0.135 0.14389) 
(list 0.135 0.15417) 
(list 0.135 0.16444) 
(list 0.135 0.17472) 
(list 0.135 0.185) 
(list 0 0.185)))
(apply 'command (append '("pline") coords '("c")))
(setq uc5 (ssadd (entlast) uc5))
(setq coords (list 
(list 1.076 -0.185) 
(list 0.538 -0.185) 
(list 0.53615 -0.17472) 
(list 0.53064 -0.16444) 
(list 0.52165 -0.15417) 
(list 0.50946 -0.14389) 
(list 0.49442 -0.13361) 
(list 0.477 -0.12333) 
(list 0.45773 -0.11306) 
(list 0.43718 -0.10278) 
(list 0.416 -0.0925) 
(list 0.39482 -0.082222) 
(list 0.37427 -0.071944) 
(list 0.355 -0.061667) 
(list 0.33758 -0.051389) 
(list 0.32254 -0.041111) 
(list 0.31034 -0.030833) 
(list 0.30136 -0.020556) 
(list 0.29585 -0.010278) 
(list 0.294 0) 
(list 0.29585 0.010278) 
(list 0.30136 0.020556) 
(list 0.31034 0.030833) 
(list 0.32254 0.041111) 
(list 0.33758 0.051389) 
(list 0.355 0.061667) 
(list 0.37427 0.071944) 
(list 0.39482 0.082222) 
(list 0.416 0.0925) 
(list 0.43718 0.10278) 
(list 0.45773 0.11306) 
(list 0.477 0.12333) 
(list 0.49442 0.13361) 
(list 0.50946 0.14389) 
(list 0.52165 0.15417) 
(list 0.53064 0.16444) 
(list 0.53615 0.17472) 
(list 0.538 0.185) 
(list 1.076 0.185)))
(apply 'command (append '("pline") coords '("c")))
(setq uc5 (ssadd (entlast) uc5))
(command "_block" "blkuc5" "0,0.185" uc5 "")
(command "_insert" "blkuc5" "1600,872.62" "1" "1" "0")
(command "_insert" "blkuc5" "1600,872.25" "1" "1" "180")
(command "_insert" "blkuc5" "1600,872.99" "1" "1" "0")
(command "_insert" "blkuc5" "1600,872.62" "1" "1" "180")
(command "_insert" "blkuc5" "1600,873.36" "1" "1" "0")
(command "_insert" "blkuc5" "1600,872.99" "1" "1" "180")
(command "_insert" "blkuc5" "1600,873.73" "1" "1" "0")
(command "_insert" "blkuc5" "1600,873.36" "1" "1" "180")
(command "_insert" "blkuc5" "1600,874.1" "1" "1" "0")
(command "_insert" "blkuc5" "1600,873.73" "1" "1" "180")
(command "_insert" "blkuc5" "1600,874.47" "1" "1" "0")
(command "_insert" "blkuc5" "1600,874.1" "1" "1" "180")
(command "_insert" "blkuc5" "1600,874.84" "1" "1" "0")
(command "_insert" "blkuc5" "1600,874.47" "1" "1" "180")
(command "_insert" "blkuc5" "1600,875.21" "1" "1" "0")
(command "_insert" "blkuc5" "1600,874.84" "1" "1" "180")
(command "_insert" "blkuc5" "1600,875.58" "1" "1" "0")
(command "_insert" "blkuc5" "1600,875.21" "1" "1" "180")
(command "_insert" "blkuc5" "1600,875.95" "1" "1" "0")
(command "_insert" "blkuc5" "1600,875.58" "1" "1" "180")
(command "_insert" "blkuc5" "1600,876.32" "1" "1" "0")
(command "_insert" "blkuc5" "1600,875.95" "1" "1" "180")
(command "_insert" "blkuc5" "1600,876.69" "1" "1" "0")
(command "_insert" "blkuc5" "1600,876.32" "1" "1" "180")
(command "_insert" "blkuc5" "1600,877.06" "1" "1" "0")
(command "_insert" "blkuc5" "1600,876.69" "1" "1" "180")
(command "_insert" "blkuc5" "1600,877.43" "1" "1" "0")
(command "_insert" "blkuc5" "1600,877.06" "1" "1" "180")
(command "_insert" "blkuc5" "1600,877.8" "1" "1" "0")
(command "_insert" "blkuc5" "1600,877.43" "1" "1" "180")
(command "_insert" "blkuc5" "1600,878.17" "1" "1" "0")
(command "_insert" "blkuc5" "1600,877.8" "1" "1" "180")
(command "_insert" "blkuc5" "1600,878.54" "1" "1" "0")
(command "_insert" "blkuc5" "1600,878.17" "1" "1" "180")
(command "_insert" "blkuc5" "1600,878.91" "1" "1" "0")
(command "_insert" "blkuc5" "1600,878.54" "1" "1" "180")
(command "_insert" "blkuc5" "1600,879.28" "1" "1" "0")
(command "_insert" "blkuc5" "1600,878.91" "1" "1" "180")
(command "_insert" "blkuc5" "1600,879.65" "1" "1" "0")
(command "_insert" "blkuc5" "1600,879.28" "1" "1" "180")
(command "_insert" "blkuc5" "1600,880.02" "1" "1" "0")
(command "_insert" "blkuc5" "1600,879.65" "1" "1" "180")
(command "_insert" "blkuc5" "1600,880.39" "1" "1" "0")
(command "_insert" "blkuc5" "1600,880.02" "1" "1" "180")
(command "_insert" "blkuc5" "1600,880.76" "1" "1" "0")
(command "_insert" "blkuc5" "1600,880.39" "1" "1" "180")
(command "_insert" "blkuc5" "1600,881.13" "1" "1" "0")
(command "_insert" "blkuc5" "1600,880.76" "1" "1" "180")
(command "_insert" "blkuc5" "1600,881.5" "1" "1" "0")
(command "_insert" "blkuc5" "1600,881.13" "1" "1" "180")
(command "_insert" "blkuc5" "1600,881.87" "1" "1" "0")
(command "_insert" "blkuc5" "1600,881.5" "1" "1" "180")
(command "_insert" "blkuc5" "1600,882.24" "1" "1" "0")
(command "_insert" "blkuc5" "1600,881.87" "1" "1" "180")
(command "_insert" "blkuc5" "1600,882.61" "1" "1" "0")
(command "_insert" "blkuc5" "1600,882.24" "1" "1" "180")
(command "_insert" "blkuc5" "1600,882.98" "1" "1" "0")
(command "_insert" "blkuc5" "1600,882.61" "1" "1" "180")
(command "_insert" "blkuc5" "1600,883.35" "1" "1" "0")
(command "_insert" "blkuc5" "1600,882.98" "1" "1" "180")
(command "_insert" "blkuc5" "1600,883.72" "1" "1" "0")
(command "_insert" "blkuc5" "1600,883.35" "1" "1" "180")
(command "_insert" "blkuc5" "1600,884.09" "1" "1" "0")
(command "_insert" "blkuc5" "1600,883.72" "1" "1" "180")
(command "_insert" "blkuc5" "1600,884.46" "1" "1" "0")
(command "_insert" "blkuc5" "1600,884.09" "1" "1" "180")
(command "_insert" "blkuc5" "1600,884.83" "1" "1" "0")
(command "_insert" "blkuc5" "1600,884.46" "1" "1" "180")
(command "_insert" "blkuc5" "1600,885.2" "1" "1" "0")
(command "_insert" "blkuc5" "1600,884.83" "1" "1" "180")
(command "_insert" "blkuc5" "1600,885.57" "1" "1" "0")
(command "_insert" "blkuc5" "1600,885.2" "1" "1" "180")
(command "_insert" "blkuc5" "1600,885.94" "1" "1" "0")
(command "_insert" "blkuc5" "1600,885.57" "1" "1" "180")
(command "_insert" "blkuc5" "1600,886.31" "1" "1" "0")
(command "_insert" "blkuc5" "1600,885.94" "1" "1" "180")
(command "_insert" "blkuc5" "1600,886.68" "1" "1" "0")
(command "_insert" "blkuc5" "1600,886.31" "1" "1" "180")
(command "_insert" "blkuc5" "1600,887.05" "1" "1" "0")
(command "_insert" "blkuc5" "1600,886.68" "1" "1" "180")
(command "_insert" "blkuc5" "1600,887.42" "1" "1" "0")
(command "_insert" "blkuc5" "1600,887.05" "1" "1" "180")
(command "_insert" "blkuc5" "1600,887.79" "1" "1" "0")
(command "_insert" "blkuc5" "1600,887.42" "1" "1" "180")
(command "_insert" "blkuc5" "1600,888.16" "1" "1" "0")
(command "_insert" "blkuc5" "1600,887.79" "1" "1" "180")
(command "_insert" "blkuc5" "1600,888.53" "1" "1" "0")
(command "_insert" "blkuc5" "1600,888.16" "1" "1" "180")
(command "_insert" "blkuc5" "1600,888.9" "1" "1" "0")
(command "_insert" "blkuc5" "1600,888.53" "1" "1" "180")
(command "_insert" "blkuc5" "1600,889.27" "1" "1" "0")
(command "_insert" "blkuc5" "1600,888.9" "1" "1" "180")
(command "_insert" "blkuc5" "1600,889.64" "1" "1" "0")
(command "_insert" "blkuc5" "1600,889.27" "1" "1" "180")
(command "_insert" "blkuc5" "1600,890.01" "1" "1" "0")
(command "_insert" "blkuc5" "1600,889.64" "1" "1" "180")
(command "_insert" "blkuc5" "1600,890.38" "1" "1" "0")
(command "_insert" "blkuc5" "1600,890.01" "1" "1" "180")
(command "_insert" "blkuc5" "1600,890.75" "1" "1" "0")
(command "_insert" "blkuc5" "1600,890.38" "1" "1" "180")
(command "_insert" "blkuc5" "1600,891.12" "1" "1" "0")
(command "_insert" "blkuc5" "1600,890.75" "1" "1" "180")
(command "_insert" "blkuc5" "1600,891.49" "1" "1" "0")
(command "_insert" "blkuc5" "1600,891.12" "1" "1" "180")
(command "_insert" "blkuc5" "1600,891.86" "1" "1" "0")
(command "_insert" "blkuc5" "1600,891.49" "1" "1" "180")
(command "_insert" "blkuc5" "1600,892.23" "1" "1" "0")
(command "_insert" "blkuc5" "1600,891.86" "1" "1" "180")
(command "_insert" "blkuc5" "1600,892.6" "1" "1" "0")
(command "_insert" "blkuc5" "1600,892.23" "1" "1" "180")
(command "_insert" "blkuc5" "1600,892.97" "1" "1" "0")
(command "_insert" "blkuc5" "1600,892.6" "1" "1" "180")
(command "_insert" "blkuc5" "1600,893.34" "1" "1" "0")
(command "_insert" "blkuc5" "1600,892.97" "1" "1" "180")
(command "_insert" "blkuc5" "1600,893.71" "1" "1" "0")
(command "_insert" "blkuc5" "1600,893.34" "1" "1" "180")
(command "_insert" "blkuc5" "1600,894.08" "1" "1" "0")
(command "_insert" "blkuc5" "1600,893.71" "1" "1" "180")
(command "_insert" "blkuc5" "1600,894.45" "1" "1" "0")
(command "_insert" "blkuc5" "1600,894.08" "1" "1" "180")
(command "_insert" "blkuc5" "1600,894.82" "1" "1" "0")
(command "_insert" "blkuc5" "1600,894.45" "1" "1" "180")
(command "_insert" "blkuc5" "1600,895.19" "1" "1" "0")
(command "_insert" "blkuc5" "1600,894.82" "1" "1" "180")
(command "_insert" "blkuc5" "1600,895.56" "1" "1" "0")
(command "_insert" "blkuc5" "1600,895.19" "1" "1" "180")
(command "_insert" "blkuc5" "1600,895.93" "1" "1" "0")
(command "_insert" "blkuc5" "1600,895.56" "1" "1" "180")
(command "_insert" "blkuc5" "1600,896.3" "1" "1" "0")
(command "_insert" "blkuc5" "1600,895.93" "1" "1" "180")
(command "_insert" "blkuc5" "1600,896.67" "1" "1" "0")
(command "_insert" "blkuc5" "1600,896.3" "1" "1" "180")
(command "_insert" "blkuc5" "1600,897.04" "1" "1" "0")
(command "_insert" "blkuc5" "1600,896.67" "1" "1" "180")
(command "_insert" "blkuc5" "1600,897.41" "1" "1" "0")
(command "_insert" "blkuc5" "1600,897.04" "1" "1" "180")
(command "_insert" "blkuc5" "1600,897.78" "1" "1" "0")
(command "_insert" "blkuc5" "1600,897.41" "1" "1" "180")
(command "_insert" "blkuc5" "1600,898.15" "1" "1" "0")
(command "_insert" "blkuc5" "1600,897.78" "1" "1" "180")
(command "_insert" "blkuc5" "1600,898.52" "1" "1" "0")
(command "_insert" "blkuc5" "1600,898.15" "1" "1" "180")
(command "_insert" "blkuc5" "1600,898.89" "1" "1" "0")
(command "_insert" "blkuc5" "1600,898.52" "1" "1" "180")
(command "_insert" "blkuc5" "1600,899.26" "1" "1" "0")
(command "_insert" "blkuc5" "1600,898.89" "1" "1" "180")
(command "_insert" "blkuc5" "1600,899.63" "1" "1" "0")
(command "_insert" "blkuc5" "1600,899.26" "1" "1" "180")
(command "_insert" "blkuc5" "1600,900" "1" "1" "0")
(command "_insert" "blkuc5" "1600,899.63" "1" "1" "180")
(command "_insert" "blkuc5" "1600,900.37" "1" "1" "0")
(command "_insert" "blkuc5" "1600,900" "1" "1" "180")
(command "_insert" "blkuc5" "1600,900.74" "1" "1" "0")
(command "_insert" "blkuc5" "1600,900.37" "1" "1" "180")
(command "_insert" "blkuc5" "1600,901.11" "1" "1" "0")
(command "_insert" "blkuc5" "1600,900.74" "1" "1" "180")
(command "_insert" "blkuc5" "1600,901.48" "1" "1" "0")
(command "_insert" "blkuc5" "1600,901.11" "1" "1" "180")
(command "_insert" "blkuc5" "1600,901.85" "1" "1" "0")
(command "_insert" "blkuc5" "1600,901.48" "1" "1" "180")
(command "_insert" "blkuc5" "1600,902.22" "1" "1" "0")
(command "_insert" "blkuc5" "1600,901.85" "1" "1" "180")
(command "_insert" "blkuc5" "1600,902.59" "1" "1" "0")
(command "_insert" "blkuc5" "1600,902.22" "1" "1" "180")
(command "_insert" "blkuc5" "1600,902.96" "1" "1" "0")
(command "_insert" "blkuc5" "1600,902.59" "1" "1" "180")
(command "_insert" "blkuc5" "1600,903.33" "1" "1" "0")
(command "_insert" "blkuc5" "1600,902.96" "1" "1" "180")
(command "_insert" "blkuc5" "1600,903.7" "1" "1" "0")
(command "_insert" "blkuc5" "1600,903.33" "1" "1" "180")
(command "_insert" "blkuc5" "1600,904.07" "1" "1" "0")
(command "_insert" "blkuc5" "1600,903.7" "1" "1" "180")
(command "_insert" "blkuc5" "1600,904.44" "1" "1" "0")
(command "_insert" "blkuc5" "1600,904.07" "1" "1" "180")
(command "_insert" "blkuc5" "1600,904.81" "1" "1" "0")
(command "_insert" "blkuc5" "1600,904.44" "1" "1" "180")
(command "_insert" "blkuc5" "1600,905.18" "1" "1" "0")
(command "_insert" "blkuc5" "1600,904.81" "1" "1" "180")
(command "_insert" "blkuc5" "1600,905.55" "1" "1" "0")
(command "_insert" "blkuc5" "1600,905.18" "1" "1" "180")
(command "_insert" "blkuc5" "1600,905.92" "1" "1" "0")
(command "_insert" "blkuc5" "1600,905.55" "1" "1" "180")
(command "_insert" "blkuc5" "1600,906.29" "1" "1" "0")
(command "_insert" "blkuc5" "1600,905.92" "1" "1" "180")
(command "_insert" "blkuc5" "1600,906.66" "1" "1" "0")
(command "_insert" "blkuc5" "1600,906.29" "1" "1" "180")
(command "_insert" "blkuc5" "1600,907.03" "1" "1" "0")
(command "_insert" "blkuc5" "1600,906.66" "1" "1" "180")
(command "_insert" "blkuc5" "1600,907.4" "1" "1" "0")
(command "_insert" "blkuc5" "1600,907.03" "1" "1" "180")
(command "_insert" "blkuc5" "1600,907.77" "1" "1" "0")
(command "_insert" "blkuc5" "1600,907.4" "1" "1" "180")
(command "_insert" "blkuc5" "1600,908.14" "1" "1" "0")
(command "_insert" "blkuc5" "1600,907.77" "1" "1" "180")
(command "_insert" "blkuc5" "1600,908.51" "1" "1" "0")
(command "_insert" "blkuc5" "1600,908.14" "1" "1" "180")
(command "_insert" "blkuc5" "1600,908.88" "1" "1" "0")
(command "_insert" "blkuc5" "1600,908.51" "1" "1" "180")
(command "_insert" "blkuc5" "1600,909.25" "1" "1" "0")
(command "_insert" "blkuc5" "1600,908.88" "1" "1" "180")
(command "_insert" "blkuc5" "1600,909.62" "1" "1" "0")
(command "_insert" "blkuc5" "1600,909.25" "1" "1" "180")
(command "_insert" "blkuc5" "1600,909.99" "1" "1" "0")
(command "_insert" "blkuc5" "1600,909.62" "1" "1" "180")
(command "_insert" "blkuc5" "1600,910.36" "1" "1" "0")
(command "_insert" "blkuc5" "1600,909.99" "1" "1" "180")
(command "_insert" "blkuc5" "1600,910.73" "1" "1" "0")
(command "_insert" "blkuc5" "1600,910.36" "1" "1" "180")
(command "_insert" "blkuc5" "1600,911.1" "1" "1" "0")
(command "_insert" "blkuc5" "1600,910.73" "1" "1" "180")
(command "_insert" "blkuc5" "1600,911.47" "1" "1" "0")
(command "_insert" "blkuc5" "1600,911.1" "1" "1" "180")
(command "_insert" "blkuc5" "1600,911.84" "1" "1" "0")
(command "_insert" "blkuc5" "1600,911.47" "1" "1" "180")
(command "_insert" "blkuc5" "1600,912.21" "1" "1" "0")
(command "_insert" "blkuc5" "1600,911.84" "1" "1" "180")
(command "_insert" "blkuc5" "1600,912.58" "1" "1" "0")
(command "_insert" "blkuc5" "1600,912.21" "1" "1" "180")
(command "_insert" "blkuc5" "1600,912.95" "1" "1" "0")
(command "_insert" "blkuc5" "1600,912.58" "1" "1" "180")
(command "_insert" "blkuc5" "1600,913.32" "1" "1" "0")
(command "_insert" "blkuc5" "1600,912.95" "1" "1" "180")
(command "_insert" "blkuc5" "1600,913.69" "1" "1" "0")
(command "_insert" "blkuc5" "1600,913.32" "1" "1" "180")
(command "_insert" "blkuc5" "1600,914.06" "1" "1" "0")
(command "_insert" "blkuc5" "1600,913.69" "1" "1" "180")
(command "_insert" "blkuc5" "1600,914.43" "1" "1" "0")
(command "_insert" "blkuc5" "1600,914.06" "1" "1" "180")
(command "_insert" "blkuc5" "1600,914.8" "1" "1" "0")
(command "_insert" "blkuc5" "1600,914.43" "1" "1" "180")
(command "_insert" "blkuc5" "1600,915.17" "1" "1" "0")
(command "_insert" "blkuc5" "1600,914.8" "1" "1" "180")
(command "_insert" "blkuc5" "1600,915.54" "1" "1" "0")
(command "_insert" "blkuc5" "1600,915.17" "1" "1" "180")
(command "_insert" "blkuc5" "1600,915.91" "1" "1" "0")
(command "_insert" "blkuc5" "1600,915.54" "1" "1" "180")
(command "_insert" "blkuc5" "1600,916.28" "1" "1" "0")
(command "_insert" "blkuc5" "1600,915.91" "1" "1" "180")
(command "_insert" "blkuc5" "1600,916.65" "1" "1" "0")
(command "_insert" "blkuc5" "1600,916.28" "1" "1" "180")
(command "_insert" "blkuc5" "1600,917.02" "1" "1" "0")
(command "_insert" "blkuc5" "1600,916.65" "1" "1" "180")
(command "_insert" "blkuc5" "1600,917.39" "1" "1" "0")
(command "_insert" "blkuc5" "1600,917.02" "1" "1" "180")
(command "_insert" "blkuc5" "1600,917.76" "1" "1" "0")
(command "_insert" "blkuc5" "1600,917.39" "1" "1" "180")
(command "_insert" "blkuc5" "1600,918.13" "1" "1" "0")
(command "_insert" "blkuc5" "1600,917.76" "1" "1" "180")
(command "_insert" "blkuc5" "1600,918.5" "1" "1" "0")
(command "_insert" "blkuc5" "1600,918.13" "1" "1" "180")
(command "_insert" "blkuc5" "1600,918.87" "1" "1" "0")
(command "_insert" "blkuc5" "1600,918.5" "1" "1" "180")
(command "_insert" "blkuc5" "1600,919.24" "1" "1" "0")
(command "_insert" "blkuc5" "1600,918.87" "1" "1" "180")
(command "_insert" "blkuc5" "1600,919.61" "1" "1" "0")
(command "_insert" "blkuc5" "1600,919.24" "1" "1" "180")
(command "_insert" "blkuc5" "1600,919.98" "1" "1" "0")
(command "_insert" "blkuc5" "1600,919.61" "1" "1" "180")
(command "_insert" "blkuc5" "1600,920.35" "1" "1" "0")
(command "_insert" "blkuc5" "1600,919.98" "1" "1" "180")
(command "_insert" "blkuc5" "1600,920.72" "1" "1" "0")
(command "_insert" "blkuc5" "1600,920.35" "1" "1" "180")
(command "_insert" "blkuc5" "1600,921.09" "1" "1" "0")
(command "_insert" "blkuc5" "1600,920.72" "1" "1" "180")
(command "_insert" "blkuc5" "1600,921.46" "1" "1" "0")
(command "_insert" "blkuc5" "1600,921.09" "1" "1" "180")
(command "_insert" "blkuc5" "1600,921.83" "1" "1" "0")
(command "_insert" "blkuc5" "1600,921.46" "1" "1" "180")
(command "_insert" "blkuc5" "1600,922.2" "1" "1" "0")
(command "_insert" "blkuc5" "1600,921.83" "1" "1" "180")
(command "_insert" "blkuc5" "1600,922.57" "1" "1" "0")
(command "_insert" "blkuc5" "1600,922.2" "1" "1" "180")
(command "_insert" "blkuc5" "1600,922.94" "1" "1" "0")
(command "_insert" "blkuc5" "1600,922.57" "1" "1" "180")
(command "_insert" "blkuc5" "1600,923.31" "1" "1" "0")
(command "_insert" "blkuc5" "1600,922.94" "1" "1" "180")
(command "_insert" "blkuc5" "1600,923.68" "1" "1" "0")
(command "_insert" "blkuc5" "1600,923.31" "1" "1" "180")
(command "_insert" "blkuc5" "1600,924.05" "1" "1" "0")
(command "_insert" "blkuc5" "1600,923.68" "1" "1" "180")
(command "_insert" "blkuc5" "1600,924.42" "1" "1" "0")
(command "_insert" "blkuc5" "1600,924.05" "1" "1" "180")
(command "_insert" "blkuc5" "1600,924.79" "1" "1" "0")
(command "_insert" "blkuc5" "1600,924.42" "1" "1" "180")
(command "_insert" "blkuc5" "1600,925.16" "1" "1" "0")
(command "_insert" "blkuc5" "1600,924.79" "1" "1" "180")
(command "_insert" "blkuc5" "1600,925.53" "1" "1" "0")
(command "_insert" "blkuc5" "1600,925.16" "1" "1" "180")
(command "_insert" "blkuc5" "1600,925.9" "1" "1" "0")
(command "_insert" "blkuc5" "1600,925.53" "1" "1" "180")
(command "_insert" "blkuc5" "1600,926.27" "1" "1" "0")
(command "_insert" "blkuc5" "1600,925.9" "1" "1" "180")
(command "_insert" "blkuc5" "1600,926.64" "1" "1" "0")
(command "_insert" "blkuc5" "1600,926.27" "1" "1" "180")
(command "_insert" "blkuc5" "1600,927.01" "1" "1" "0")
(command "_insert" "blkuc5" "1600,926.64" "1" "1" "180")
(command "_insert" "blkuc5" "1600,927.38" "1" "1" "0")
(command "_insert" "blkuc5" "1600,927.01" "1" "1" "180")
(command "_insert" "blkuc5" "1600,927.75" "1" "1" "0")
(command "_insert" "blkuc5" "1600,927.38" "1" "1" "180")
(command "_layer" "set" "phccover" "")
(command "_rectangle" "1598.924,933.3" "1601.076,866.7")
(command "_layer" "set" "nitride" "")
(setq phc5 currobj)
(command "_layer" "set" "cover" "")
(command "_rectangle" "1598.924,836.7" "1601.076,963.3")
(command "_layer" "set" "nitride" "")
(command "_layer" "set" "text" "")
(command "_circle" "1597.974,846.7" "0.075")
(command "_circle" "1597.599,846.7" "0.15")
(command "_circle" "1597.224,846.7" "0.075")
(command "_circle" "1596.849,846.7" "0.15")
(command "_circle" "1597.974,848.7" "0.075")
(command "_circle" "1597.599,848.7" "0.075")
(command "_circle" "1597.224,848.7" "0.15")
(command "_circle" "1596.849,848.7" "0.15")
(command "_circle" "1597.974,850.7" "0.075")
(command "_circle" "1597.599,850.7" "0.15")
(command "_circle" "1597.224,850.7" "0.15")
(command "_circle" "1596.849,850.7" "0.15")
(command "_circle" "1597.974,852.7" "0.075")
(command "_circle" "1597.599,852.7" "0.075")
(command "_circle" "1597.224,852.7" "0.075")
(command "_circle" "1596.849,852.7" "0.075")
(command "_circle" "1596.474,852.7" "0.15")
(command "_circle" "1597.974,854.7" "0.075")
(command "_circle" "1597.599,854.7" "0.15")
(command "_circle" "1597.224,854.7" "0.075")
(command "_circle" "1596.849,854.7" "0.075")
(command "_circle" "1596.474,854.7" "0.15")
(command "_circle" "1597.974,856.7" "0.075")
(command "_circle" "1597.599,856.7" "0.075")
(command "_circle" "1597.224,856.7" "0.15")
(command "_circle" "1596.849,856.7" "0.075")
(command "_circle" "1596.474,856.7" "0.15")
(command "_circle" "1597.974,858.7" "0.075")
(command "_circle" "1597.599,858.7" "0.15")
(command "_circle" "1597.224,858.7" "0.15")
(command "_circle" "1596.849,858.7" "0.075")
(command "_circle" "1596.474,858.7" "0.15")
(command "_circle" "1597.974,860.7" "0.075")
(command "_circle" "1597.599,860.7" "0.075")
(command "_circle" "1597.224,860.7" "0.075")
(command "_circle" "1596.849,860.7" "0.15")
(command "_circle" "1596.474,860.7" "0.15")
(command "_circle" "1597.974,862.7" "0.075")
(command "_circle" "1597.599,862.7" "0.15")
(command "_circle" "1597.224,862.7" "0.075")
(command "_circle" "1596.849,862.7" "0.15")
(command "_circle" "1596.474,862.7" "0.15")
(command "_circle" "1597.974,864.7" "0.075")
(command "_circle" "1597.599,864.7" "0.075")
(command "_circle" "1597.224,864.7" "0.15")
(command "_circle" "1596.849,864.7" "0.15")
(command "_circle" "1596.474,864.7" "0.15")
(command "_circle" "1597.974,866.7" "0.075")
(command "_circle" "1597.599,866.7" "0.15")
(command "_circle" "1597.224,866.7" "0.15")
(command "_circle" "1596.849,866.7" "0.15")
(command "_circle" "1596.474,866.7" "0.15")
(command "_circle" "1597.974,868.7" "0.075")
(command "_circle" "1597.599,868.7" "0.075")
(command "_circle" "1597.224,868.7" "0.075")
(command "_circle" "1596.849,868.7" "0.075")
(command "_circle" "1596.474,868.7" "0.075")
(command "_circle" "1596.099,868.7" "0.15")
(command "_circle" "1597.974,870.7" "0.075")
(command "_circle" "1597.599,870.7" "0.15")
(command "_circle" "1597.224,870.7" "0.075")
(command "_circle" "1596.849,870.7" "0.075")
(command "_circle" "1596.474,870.7" "0.075")
(command "_circle" "1596.099,870.7" "0.15")
(command "_circle" "1597.974,872.7" "0.075")
(command "_circle" "1597.599,872.7" "0.075")
(command "_circle" "1597.224,872.7" "0.15")
(command "_circle" "1596.849,872.7" "0.075")
(command "_circle" "1596.474,872.7" "0.075")
(command "_circle" "1596.099,872.7" "0.15")
(command "_circle" "1597.974,874.7" "0.075")
(command "_circle" "1597.599,874.7" "0.15")
(command "_circle" "1597.224,874.7" "0.15")
(command "_circle" "1596.849,874.7" "0.075")
(command "_circle" "1596.474,874.7" "0.075")
(command "_circle" "1596.099,874.7" "0.15")
(command "_circle" "1597.974,876.7" "0.075")
(command "_circle" "1597.599,876.7" "0.075")
(command "_circle" "1597.224,876.7" "0.075")
(command "_circle" "1596.849,876.7" "0.15")
(command "_circle" "1596.474,876.7" "0.075")
(command "_circle" "1596.099,876.7" "0.15")
(command "_circle" "1597.974,878.7" "0.075")
(command "_circle" "1597.599,878.7" "0.15")
(command "_circle" "1597.224,878.7" "0.075")
(command "_circle" "1596.849,878.7" "0.15")
(command "_circle" "1596.474,878.7" "0.075")
(command "_circle" "1596.099,878.7" "0.15")
(command "_circle" "1597.974,880.7" "0.075")
(command "_circle" "1597.599,880.7" "0.075")
(command "_circle" "1597.224,880.7" "0.15")
(command "_circle" "1596.849,880.7" "0.15")
(command "_circle" "1596.474,880.7" "0.075")
(command "_circle" "1596.099,880.7" "0.15")
(command "_circle" "1597.974,882.7" "0.075")
(command "_circle" "1597.599,882.7" "0.15")
(command "_circle" "1597.224,882.7" "0.15")
(command "_circle" "1596.849,882.7" "0.15")
(command "_circle" "1596.474,882.7" "0.075")
(command "_circle" "1596.099,882.7" "0.15")
(command "_circle" "1597.974,884.7" "0.075")
(command "_circle" "1597.599,884.7" "0.075")
(command "_circle" "1597.224,884.7" "0.075")
(command "_circle" "1596.849,884.7" "0.075")
(command "_circle" "1596.474,884.7" "0.15")
(command "_circle" "1596.099,884.7" "0.15")
(command "_circle" "1597.974,886.7" "0.075")
(command "_circle" "1597.599,886.7" "0.15")
(command "_circle" "1597.224,886.7" "0.075")
(command "_circle" "1596.849,886.7" "0.075")
(command "_circle" "1596.474,886.7" "0.15")
(command "_circle" "1596.099,886.7" "0.15")
(command "_circle" "1597.974,888.7" "0.075")
(command "_circle" "1597.599,888.7" "0.075")
(command "_circle" "1597.224,888.7" "0.15")
(command "_circle" "1596.849,888.7" "0.075")
(command "_circle" "1596.474,888.7" "0.15")
(command "_circle" "1596.099,888.7" "0.15")
(command "_circle" "1597.974,890.7" "0.075")
(command "_circle" "1597.599,890.7" "0.15")
(command "_circle" "1597.224,890.7" "0.15")
(command "_circle" "1596.849,890.7" "0.075")
(command "_circle" "1596.474,890.7" "0.15")
(command "_circle" "1596.099,890.7" "0.15")
(command "_circle" "1597.974,892.7" "0.075")
(command "_circle" "1597.599,892.7" "0.075")
(command "_circle" "1597.224,892.7" "0.075")
(command "_circle" "1596.849,892.7" "0.15")
(command "_circle" "1596.474,892.7" "0.15")
(command "_circle" "1596.099,892.7" "0.15")
(command "_circle" "1597.974,894.7" "0.075")
(command "_circle" "1597.599,894.7" "0.15")
(command "_circle" "1597.224,894.7" "0.075")
(command "_circle" "1596.849,894.7" "0.15")
(command "_circle" "1596.474,894.7" "0.15")
(command "_circle" "1596.099,894.7" "0.15")
(command "_circle" "1597.974,896.7" "0.075")
(command "_circle" "1597.599,896.7" "0.075")
(command "_circle" "1597.224,896.7" "0.15")
(command "_circle" "1596.849,896.7" "0.15")
(command "_circle" "1596.474,896.7" "0.15")
(command "_circle" "1596.099,896.7" "0.15")
(command "_circle" "1597.974,898.7" "0.075")
(command "_circle" "1597.599,898.7" "0.15")
(command "_circle" "1597.224,898.7" "0.15")
(command "_circle" "1596.849,898.7" "0.15")
(command "_circle" "1596.474,898.7" "0.15")
(command "_circle" "1596.099,898.7" "0.15")
(command "_circle" "1597.974,900.7" "0.075")
(command "_circle" "1597.599,900.7" "0.075")
(command "_circle" "1597.224,900.7" "0.075")
(command "_circle" "1596.849,900.7" "0.075")
(command "_circle" "1596.474,900.7" "0.075")
(command "_circle" "1596.099,900.7" "0.075")
(command "_circle" "1595.724,900.7" "0.15")
(command "_circle" "1597.974,902.7" "0.075")
(command "_circle" "1597.599,902.7" "0.15")
(command "_circle" "1597.224,902.7" "0.075")
(command "_circle" "1596.849,902.7" "0.075")
(command "_circle" "1596.474,902.7" "0.075")
(command "_circle" "1596.099,902.7" "0.075")
(command "_circle" "1595.724,902.7" "0.15")
(command "_circle" "1597.974,904.7" "0.075")
(command "_circle" "1597.599,904.7" "0.075")
(command "_circle" "1597.224,904.7" "0.15")
(command "_circle" "1596.849,904.7" "0.075")
(command "_circle" "1596.474,904.7" "0.075")
(command "_circle" "1596.099,904.7" "0.075")
(command "_circle" "1595.724,904.7" "0.15")
(command "_circle" "1597.974,906.7" "0.075")
(command "_circle" "1597.599,906.7" "0.15")
(command "_circle" "1597.224,906.7" "0.15")
(command "_circle" "1596.849,906.7" "0.075")
(command "_circle" "1596.474,906.7" "0.075")
(command "_circle" "1596.099,906.7" "0.075")
(command "_circle" "1595.724,906.7" "0.15")
(command "_circle" "1597.974,908.7" "0.075")
(command "_circle" "1597.599,908.7" "0.075")
(command "_circle" "1597.224,908.7" "0.075")
(command "_circle" "1596.849,908.7" "0.15")
(command "_circle" "1596.474,908.7" "0.075")
(command "_circle" "1596.099,908.7" "0.075")
(command "_circle" "1595.724,908.7" "0.15")
(command "_circle" "1597.974,910.7" "0.075")
(command "_circle" "1597.599,910.7" "0.15")
(command "_circle" "1597.224,910.7" "0.075")
(command "_circle" "1596.849,910.7" "0.15")
(command "_circle" "1596.474,910.7" "0.075")
(command "_circle" "1596.099,910.7" "0.075")
(command "_circle" "1595.724,910.7" "0.15")
(command "_circle" "1597.974,912.7" "0.075")
(command "_circle" "1597.599,912.7" "0.075")
(command "_circle" "1597.224,912.7" "0.15")
(command "_circle" "1596.849,912.7" "0.15")
(command "_circle" "1596.474,912.7" "0.075")
(command "_circle" "1596.099,912.7" "0.075")
(command "_circle" "1595.724,912.7" "0.15")
(command "_circle" "1597.974,914.7" "0.075")
(command "_circle" "1597.599,914.7" "0.15")
(command "_circle" "1597.224,914.7" "0.15")
(command "_circle" "1596.849,914.7" "0.15")
(command "_circle" "1596.474,914.7" "0.075")
(command "_circle" "1596.099,914.7" "0.075")
(command "_circle" "1595.724,914.7" "0.15")
(command "_circle" "1597.974,916.7" "0.075")
(command "_circle" "1597.599,916.7" "0.075")
(command "_circle" "1597.224,916.7" "0.075")
(command "_circle" "1596.849,916.7" "0.075")
(command "_circle" "1596.474,916.7" "0.15")
(command "_circle" "1596.099,916.7" "0.075")
(command "_circle" "1595.724,916.7" "0.15")
(command "_circle" "1597.974,918.7" "0.075")
(command "_circle" "1597.599,918.7" "0.15")
(command "_circle" "1597.224,918.7" "0.075")
(command "_circle" "1596.849,918.7" "0.075")
(command "_circle" "1596.474,918.7" "0.15")
(command "_circle" "1596.099,918.7" "0.075")
(command "_circle" "1595.724,918.7" "0.15")
(command "_circle" "1597.974,920.7" "0.075")
(command "_circle" "1597.599,920.7" "0.075")
(command "_circle" "1597.224,920.7" "0.15")
(command "_circle" "1596.849,920.7" "0.075")
(command "_circle" "1596.474,920.7" "0.15")
(command "_circle" "1596.099,920.7" "0.075")
(command "_circle" "1595.724,920.7" "0.15")
(command "_circle" "1597.974,922.7" "0.075")
(command "_circle" "1597.599,922.7" "0.15")
(command "_circle" "1597.224,922.7" "0.15")
(command "_circle" "1596.849,922.7" "0.075")
(command "_circle" "1596.474,922.7" "0.15")
(command "_circle" "1596.099,922.7" "0.075")
(command "_circle" "1595.724,922.7" "0.15")
(command "_circle" "1597.974,924.7" "0.075")
(command "_circle" "1597.599,924.7" "0.075")
(command "_circle" "1597.224,924.7" "0.075")
(command "_circle" "1596.849,924.7" "0.15")
(command "_circle" "1596.474,924.7" "0.15")
(command "_circle" "1596.099,924.7" "0.075")
(command "_circle" "1595.724,924.7" "0.15")
(command "_circle" "1597.974,926.7" "0.075")
(command "_circle" "1597.599,926.7" "0.15")
(command "_circle" "1597.224,926.7" "0.075")
(command "_circle" "1596.849,926.7" "0.15")
(command "_circle" "1596.474,926.7" "0.15")
(command "_circle" "1596.099,926.7" "0.075")
(command "_circle" "1595.724,926.7" "0.15")
(command "_circle" "1597.974,928.7" "0.075")
(command "_circle" "1597.599,928.7" "0.075")
(command "_circle" "1597.224,928.7" "0.15")
(command "_circle" "1596.849,928.7" "0.15")
(command "_circle" "1596.474,928.7" "0.15")
(command "_circle" "1596.099,928.7" "0.075")
(command "_circle" "1595.724,928.7" "0.15")
(command "_circle" "1597.974,930.7" "0.075")
(command "_circle" "1597.599,930.7" "0.15")
(command "_circle" "1597.224,930.7" "0.15")
(command "_circle" "1596.849,930.7" "0.15")
(command "_circle" "1596.474,930.7" "0.15")
(command "_circle" "1596.099,930.7" "0.075")
(command "_circle" "1595.724,930.7" "0.15")
(command "_circle" "1597.974,932.7" "0.075")
(command "_circle" "1597.599,932.7" "0.075")
(command "_circle" "1597.224,932.7" "0.075")
(command "_circle" "1596.849,932.7" "0.075")
(command "_circle" "1596.474,932.7" "0.075")
(command "_circle" "1596.099,932.7" "0.15")
(command "_circle" "1595.724,932.7" "0.15")
(command "_circle" "1597.974,934.7" "0.075")
(command "_circle" "1597.599,934.7" "0.15")
(command "_circle" "1597.224,934.7" "0.075")
(command "_circle" "1596.849,934.7" "0.075")
(command "_circle" "1596.474,934.7" "0.075")
(command "_circle" "1596.099,934.7" "0.15")
(command "_circle" "1595.724,934.7" "0.15")
(command "_circle" "1597.974,936.7" "0.075")
(command "_circle" "1597.599,936.7" "0.075")
(command "_circle" "1597.224,936.7" "0.15")
(command "_circle" "1596.849,936.7" "0.075")
(command "_circle" "1596.474,936.7" "0.075")
(command "_circle" "1596.099,936.7" "0.15")
(command "_circle" "1595.724,936.7" "0.15")
(command "_circle" "1597.974,938.7" "0.075")
(command "_circle" "1597.599,938.7" "0.15")
(command "_circle" "1597.224,938.7" "0.15")
(command "_circle" "1596.849,938.7" "0.075")
(command "_circle" "1596.474,938.7" "0.075")
(command "_circle" "1596.099,938.7" "0.15")
(command "_circle" "1595.724,938.7" "0.15")
(command "_circle" "1597.974,940.7" "0.075")
(command "_circle" "1597.599,940.7" "0.075")
(command "_circle" "1597.224,940.7" "0.075")
(command "_circle" "1596.849,940.7" "0.15")
(command "_circle" "1596.474,940.7" "0.075")
(command "_circle" "1596.099,940.7" "0.15")
(command "_circle" "1595.724,940.7" "0.15")
(command "_circle" "1597.974,942.7" "0.075")
(command "_circle" "1597.599,942.7" "0.15")
(command "_circle" "1597.224,942.7" "0.075")
(command "_circle" "1596.849,942.7" "0.15")
(command "_circle" "1596.474,942.7" "0.075")
(command "_circle" "1596.099,942.7" "0.15")
(command "_circle" "1595.724,942.7" "0.15")
(command "_circle" "1597.974,944.7" "0.075")
(command "_circle" "1597.599,944.7" "0.075")
(command "_circle" "1597.224,944.7" "0.15")
(command "_circle" "1596.849,944.7" "0.15")
(command "_circle" "1596.474,944.7" "0.075")
(command "_circle" "1596.099,944.7" "0.15")
(command "_circle" "1595.724,944.7" "0.15")
(command "_circle" "1597.974,946.7" "0.075")
(command "_circle" "1597.599,946.7" "0.15")
(command "_circle" "1597.224,946.7" "0.15")
(command "_circle" "1596.849,946.7" "0.15")
(command "_circle" "1596.474,946.7" "0.075")
(command "_circle" "1596.099,946.7" "0.15")
(command "_circle" "1595.724,946.7" "0.15")
(command "_circle" "1597.974,948.7" "0.075")
(command "_circle" "1597.599,948.7" "0.075")
(command "_circle" "1597.224,948.7" "0.075")
(command "_circle" "1596.849,948.7" "0.075")
(command "_circle" "1596.474,948.7" "0.15")
(command "_circle" "1596.099,948.7" "0.15")
(command "_circle" "1595.724,948.7" "0.15")
(command "_circle" "1597.974,950.7" "0.075")
(command "_circle" "1597.599,950.7" "0.15")
(command "_circle" "1597.224,950.7" "0.075")
(command "_circle" "1596.849,950.7" "0.075")
(command "_circle" "1596.474,950.7" "0.15")
(command "_circle" "1596.099,950.7" "0.15")
(command "_circle" "1595.724,950.7" "0.15")
(command "_circle" "1597.974,952.7" "0.075")
(command "_circle" "1597.599,952.7" "0.075")
(command "_circle" "1597.224,952.7" "0.15")
(command "_circle" "1596.849,952.7" "0.075")
(command "_circle" "1596.474,952.7" "0.15")
(command "_circle" "1596.099,952.7" "0.15")
(command "_circle" "1595.724,952.7" "0.15")
(command "_circle" "1597.974,954.7" "0.075")
(command "_circle" "1597.599,954.7" "0.15")
(command "_circle" "1597.224,954.7" "0.15")
(command "_circle" "1596.849,954.7" "0.075")
(command "_circle" "1596.474,954.7" "0.15")
(command "_circle" "1596.099,954.7" "0.15")
(command "_circle" "1595.724,954.7" "0.15")
(command "_circle" "1597.974,956.7" "0.075")
(command "_circle" "1597.599,956.7" "0.075")
(command "_circle" "1597.224,956.7" "0.075")
(command "_circle" "1596.849,956.7" "0.15")
(command "_circle" "1596.474,956.7" "0.15")
(command "_circle" "1596.099,956.7" "0.15")
(command "_circle" "1595.724,956.7" "0.15")
(command "_circle" "1597.974,958.7" "0.075")
(command "_circle" "1597.599,958.7" "0.15")
(command "_circle" "1597.224,958.7" "0.075")
(command "_circle" "1596.849,958.7" "0.15")
(command "_circle" "1596.474,958.7" "0.15")
(command "_circle" "1596.099,958.7" "0.15")
(command "_circle" "1595.724,958.7" "0.15")
(command "_circle" "1597.974,960.7" "0.075")
(command "_circle" "1597.599,960.7" "0.075")
(command "_circle" "1597.224,960.7" "0.15")
(command "_circle" "1596.849,960.7" "0.15")
(command "_circle" "1596.474,960.7" "0.15")
(command "_circle" "1596.099,960.7" "0.15")
(command "_circle" "1595.724,960.7" "0.15")
(command "_circle" "1597.974,962.7" "0.075")
(command "_circle" "1597.599,962.7" "0.15")
(command "_circle" "1597.224,962.7" "0.15")
(command "_circle" "1596.849,962.7" "0.15")
(command "_circle" "1596.474,962.7" "0.15")
(command "_circle" "1596.099,962.7" "0.15")
(command "_circle" "1595.724,962.7" "0.15")
(command "_layer" "set" "nitride" "")
(command "_layer" "set" "text" "")
(command-s "_text" "1586.924,963.3" "2" "-90" "a = 370 nm" )
(sssetfirst nil (ssget "_L"))
(if (not (numberp (vl-string-search "Mac" (getvar "platform")))) (c:txtexp))
(command "_layer" "set" "nitride" "")
(command "_layer" "set" "text" "")
(command-s "_text" "1583.924,963.3" "2" "-90" "gap = 270 nm" )
(sssetfirst nil (ssget "_L"))
(if (not (numberp (vl-string-search "Mac" (getvar "platform")))) (c:txtexp))
(command "_layer" "set" "nitride" "")
(command "_layer" "set" "text" "")
(command-s "_text" "1580.924,963.3" "2" "-90" "amplitude = 122 nm" )
(sssetfirst nil (ssget "_L"))
(if (not (numberp (vl-string-search "Mac" (getvar "platform")))) (c:txtexp))
(command "_layer" "set" "nitride" "")
(command "_layer" "set" "text" "")
(command-s "_text" "1577.924,963.3" "2" "-90" "start width = 280 nm" )
(sssetfirst nil (ssget "_L"))
(if (not (numberp (vl-string-search "Mac" (getvar "platform")))) (c:txtexp))
(command "_layer" "set" "nitride" "")
(command "_layer" "set" "text" "")
(command-s "_text" "1574.924,963.3" "2" "-90" "width = 281 nm" )
(sssetfirst nil (ssget "_L"))
(if (not (numberp (vl-string-search "Mac" (getvar "platform")))) (c:txtexp))
(command "_layer" "set" "nitride" "")
(command "_layer" "set" "text" "")
(command-s "_text" "1571.924,963.3" "2" "-90" "taper: 15" )
(sssetfirst nil (ssget "_L"))
(if (not (numberp (vl-string-search "Mac" (getvar "platform")))) (c:txtexp))
(command "_layer" "set" "nitride" "")
(command "_layer" "set" "text" "")
(command-s "_text" "1568.924,963.3" "2" "-90" "nominal: 150" )
(sssetfirst nil (ssget "_L"))
(if (not (numberp (vl-string-search "Mac" (getvar "platform")))) (c:txtexp))
(command "_layer" "set" "nitride" "")
(command "_layer" "set" "indicators" "")
(setq coords (list 
(list 1520.415 940) 
(list 1520.415 920) 
(list 1500.415 900) 
(list 1520.415 880) 
(list 1520.415 860) 
(list 1520.415 900) 
(list 1520.415 887.0711) 
(list 1507.4861 900) 
(list 1520.415 912.9289) 
(list 1520.415 900)))
(apply 'command (append '("pline") coords '("c")))
(command "._fillet" "radius" "1" "._fillet" "P" (entlast))
(setq coords (list 
(list 1679.585 940) 
(list 1679.585 920) 
(list 1699.585 900) 
(list 1679.585 880) 
(list 1679.585 860) 
(list 1679.585 900) 
(list 1679.585 887.0711) 
(list 1692.5139 900) 
(list 1679.585 912.9289) 
(list 1679.585 900)))
(apply 'command (append '("pline") coords '("c")))
(command "._fillet" "radius" "1" "._fillet" "P" (entlast))
(command "_layer" "set" "holes" "")
(command "_circle" "1518.0629,914.1124" "0.5")
(command "_circle" "1515.7109,911.7603" "0.5")
(command "_circle" "1513.3588,909.4083" "0.5")
(command "_circle" "1511.0067,907.0562" "0.5")
(command "_circle" "1508.6547,904.7041" "0.5")
(command "_circle" "1506.3026,902.3521" "0.5")
(command "_circle" "1503.9505,900" "0.5")
(command "_circle" "1506.3026,897.6479" "0.5")
(command "_circle" "1508.6547,895.2959" "0.5")
(command "_circle" "1511.0067,892.9438" "0.5")
(command "_circle" "1513.3588,890.5917" "0.5")
(command "_circle" "1515.7109,888.2397" "0.5")
(command "_circle" "1518.0629,885.8876" "0.5")
(command "_circle" "1681.9371,914.1124" "0.5")
(command "_circle" "1684.2891,911.7603" "0.5")
(command "_circle" "1686.6412,909.4083" "0.5")
(command "_circle" "1688.9933,907.0562" "0.5")
(command "_circle" "1691.3453,904.7041" "0.5")
(command "_circle" "1693.6974,902.3521" "0.5")
(command "_circle" "1696.0495,900" "0.5")
(command "_circle" "1693.6974,897.6479" "0.5")
(command "_circle" "1691.3453,895.2959" "0.5")
(command "_circle" "1688.9933,892.9438" "0.5")
(command "_circle" "1686.6412,890.5917" "0.5")
(command "_circle" "1684.2891,888.2397" "0.5")
(command "_circle" "1681.9371,885.8876" "0.5")
(command "_layer" "set" "nitride" "")
(command "_block" "blkcoupler5" "1600,900" coupler5 "")
(command "_insert" "blkcoupler5" "1600,900" "1" "1" "0")
(command "_insert" "blkcoupler5" "1600,900" "1" "1" "180")
(command "_block" "blksinglenanobeam5" "1600,900" singlenanobeam5 "")
(command "_insert" "blksinglenanobeam5" "1600,900" "1" "1" "0")
(command "_insert" "blksinglenanobeam5" "1600,900" "1" "1" "180")
(command "_block" "blkanglednodearray5" "1600,900" anglednodearray5 "")
(command "_insert" "blkanglednodearray5" "1600,900" "1" "1" "0")
(command "_insert" "blkanglednodearray5" "1600,900" "1" "1" "180")
(command "_block" "blkcooledsinglenanobeam5" "1600,900" cooledsinglenanobeam5 "")
(command "_insert" "blkcooledsinglenanobeam5" "1600,900" "1" "1" "0")
(command "_insert" "blkcooledsinglenanobeam5" "1600,900" "1" "1" "180")
(command "_block" "blkyjunction5" "1600,900" yjunction5 "")
(command "_insert" "blkyjunction5" "1600,900" "1" "1" "0")
(command "_insert" "blkyjunction5" "1600,900" "1" "1" "180")
; DRAWING BULGING VEE GROOVE
(command "_layer" "set" "vgroove" "")
(setq coords (list 
(list 1525.415 -605) 
(list 1525.415 0) 
(list 1525.415 0) 
(list 1525.415 1800) 
(list 1525.415 1800) 
(list 1525.415 2405) 
(list 1674.585 2405) 
(list 1674.585 1800) 
(list 1674.585 1800) 
(list 1674.585 0) 
(list 1674.585 0) 
(list 1674.585 -605)))
(apply 'command (append '("pline") coords '("c")))
(command "._fillet" "radius" "0" "._fillet" "P" (entlast))
(command "_layer" "set" "window" "")
(command "_rectangle" "1525.415,-1935" "1674.585,-600")
(command "_rectangle" "1525.415,2400" "1674.585,5300")
(command "_layer" "set" "grid" "")
(command "_rectangle" "1526.415,-1934" "1549.9433,-1909.2133")
(command "_array" "last" "" "R" "75" "3" "25.7867" "24.5283")
(command "_rectangle" "1601,-1934" "1624.5283,-1909.2133")
(command "_array" "last" "" "R" "75" "3" "25.7867" "24.5283")
(command "_rectangle" "1526.415,1" "1549.9433,25.7")
(command "_array" "last" "" "R" "70" "3" "25.7" "24.5283")
(command "_rectangle" "1601,1" "1624.5283,25.7")
(command "_array" "last" "" "R" "70" "3" "25.7" "24.5283")
(command "_rectangle" "1526.415,1801" "1549.9433,1825.9185")
(command "_array" "last" "" "R" "135" "3" "25.9185" "24.5283")
(command "_rectangle" "1601,1801" "1624.5283,1825.9185")
(command "_array" "last" "" "R" "135" "3" "25.9185" "24.5283")
(command "_layer" "set" "vgrooveFDA" "")
(command "_rectangle" "1674.585,-2233" "1525.415,-1933")
(command "_layer" "set" "nitride" "")
(command "_layer" "set" "holes" "")
(command "_circle" "1677.085,331.5" "0.5")
(command "_array" "last" "" "R" "379" "1" "3" "2.5")
(command "_circle" "1522.915,331.5" "0.5")
(command "_array" "last" "" "R" "379" "1" "3" "-2.5")
(command "_layer" "set" "nitride" "")
(command "_layer" "set" "window" "")
(command "_layer" "set" "window" "")
(command "_rectangle" "1679.585,0" "1840.415,1800")
(command "._fillet" "radius" "20" "._fillet" "P" (entlast))
(command "_layer" "set" "grid" "")
(command "_rectangle" "1680.585,1" "1702.4179,25.7")
(command "_array" "last" "" "R" "70" "7" "25.7" "22.8329")
(command "_layer" "set" "nitride" "")
; DRAWING REGION LAYER
(command "_layer" "set" "regionLayer5" "")
(command "_rectangle" "1520,-460" "1680,2260")
(command "_layer" "set" "nitride" "")
(setq coupler5 nil)
(setq singlenanobeam5 nil)
(setq anglednodearray5 nil)
(setq cooledsinglenanobeam5 nil)
(setq yjunction5 nil)
; DEVICE #6
(command "_layer" "set" "window" "")
(command "_circle" "1832.915,-415" "5")
(command "_circle" "1832.915,-402.5" "5")
(command "_circle" "1832.915,-390" "5")
(command "_circle" "1832.915,-377.5" "5")
(command "_circle" "1820.415,-415" "5")
(command "_circle" "1820.415,-402.5" "5")
(command "_layer" "set" "nitride" "")
(setq currobj nil)
(setq currobj (ssadd))
; DRAWING COUPLER
(setq coords (list 
(list 1920.0595 -415) 
(list 1920.0595 -413) 
(list 1993.585 -413) 
(list 1993.585 -413) 
(list 1993.9677 -413.0761) 
(list 1994.2921 -413.2929) 
(list 1994.5089 -413.6173) 
(list 1994.585 -414) 
(list 1994.585 -411.8) 
(list 1994.585 -411.8) 
(list 1994.5089 -412.1827) 
(list 1994.2921 -412.5071) 
(list 1993.9677 -412.7239) 
(list 1993.585 -412.8) 
(list 1920.0595 -412.8) 
(list 1920.0595 -410.8) 
(list 1919.9405 -410.8) 
(list 1919.9405 -412.8) 
(list 1846.415 -412.8) 
(list 1846.0323 -412.7239) 
(list 1845.7079 -412.5071) 
(list 1845.4911 -412.1827) 
(list 1845.415 -411.8) 
(list 1845.415 -411.8) 
(list 1845.415 -414) 
(list 1845.4911 -413.6173) 
(list 1845.7079 -413.2929) 
(list 1846.0323 -413.0761) 
(list 1846.415 -413) 
(list 1846.415 -413) 
(list 1919.9405 -413) 
(list 1919.9405 -415)))
(apply 'command (append '("pline") coords '("c")))
(setq currobj (ssadd (entlast) currobj))
(command "._fillet" "radius" "0.3" "._fillet" "P" (entlast))
(command "_layer" "set" "holes" "")
(command "_circle" "1920,-412.9" "0.113")
(setq currobj (ssadd (entlast) currobj))
(command "_layer" "set" "nitride" "")
(command "_layer" "set" "text" "")
(command "_circle" "1919.2,-415" "0.075")
(command "_circle" "1919.2,-414.7" "0.075")
(command "_circle" "1919.2,-414.4" "0.075")
(command "_circle" "1918.9,-415" "0.075")
(command "_circle" "1918.9,-414.7" "0.075")
(command "_circle" "1918.9,-414.4" "0.075")
(command "_circle" "1918.6,-415" "0.075")
(command "_circle" "1918.6,-414.7" "0.075")
(command "_circle" "1918.6,-414.4" "0.075")
(command "_layer" "set" "nitride" "")
(command "_layer" "set" "prebias" "")
(command "_rectangle" "1845.415,-414" "1994.585,-411.8")
(setq currobj (ssadd (entlast) currobj))
(command "_rectangle" "1919.9405,-415" "1920.0595,-410.8")
(setq currobj (ssadd (entlast) currobj))
(command "_layer" "set" "nitride" "")
(setq coupler6 currobj)
(setq currobj nil)
(setq currobj (ssadd))
; DRAWING SINGLE NANOBEAM
(setq coords (list 
(list 1920.0595 -410.8) 
(list 1920.0595 -409.1417) 
(list 1920.0595 -407.4833) 
(list 1920.0595 -405.825) 
(list 1920.0595 -404.1667) 
(list 1920.0595 -402.5083) 
(list 1920.0595 -400.85) 
(list 1920.0595 -399.1917) 
(list 1920.0595 -397.5333) 
(list 1920.0596 -395.875) 
(list 1920.0596 -394.2167) 
(list 1920.0596 -392.5583) 
(list 1920.0596 -390.9) 
(list 1920.0597 -389.2417) 
(list 1920.0597 -387.5833) 
(list 1920.0597 -385.925) 
(list 1920.0598 -384.2667) 
(list 1920.0599 -382.6083) 
(list 1920.0599 -380.95) 
(list 1920.06 -379.2917) 
(list 1920.0601 -377.6333) 
(list 1920.0602 -375.975) 
(list 1920.0603 -374.3167) 
(list 1920.0604 -372.6583) 
(list 1920.0605 -371) 
(list 1920.0606 -369.3417) 
(list 1920.0608 -367.6833) 
(list 1920.0609 -366.025) 
(list 1920.0611 -364.3667) 
(list 1920.0613 -362.7083) 
(list 1920.0615 -361.05) 
(list 1920.0617 -359.3917) 
(list 1920.0619 -357.7333) 
(list 1920.0621 -356.075) 
(list 1920.0624 -354.4167) 
(list 1920.0626 -352.7583) 
(list 1920.0629 -351.1) 
(list 1920.0632 -349.4417) 
(list 1920.0635 -347.7833) 
(list 1920.0638 -346.125) 
(list 1920.0641 -344.4667) 
(list 1920.0645 -342.8083) 
(list 1920.0649 -341.15) 
(list 1920.0653 -339.4917) 
(list 1920.0657 -337.8333) 
(list 1920.0661 -336.175) 
(list 1920.0666 -334.5167) 
(list 1920.067 -332.8583) 
(list 1920.0675 -331.2) 
(list 1920.068 -329.5417) 
(list 1920.0686 -327.8833) 
(list 1920.0691 -326.225) 
(list 1920.0697 -324.5667) 
(list 1920.0703 -322.9083) 
(list 1920.0709 -321.25) 
(list 1920.0716 -319.5917) 
(list 1920.0723 -317.9333) 
(list 1920.0729 -316.275) 
(list 1920.0737 -314.6167) 
(list 1920.0744 -312.9583) 
(list 1920.0752 -311.3) 
(list 1920.076 -309.6417) 
(list 1920.0768 -307.9833) 
(list 1920.0777 -306.325) 
(list 1920.0785 -304.6667) 
(list 1920.0794 -303.0083) 
(list 1920.0804 -301.35) 
(list 1920.0813 -299.6917) 
(list 1920.0823 -298.0333) 
(list 1920.0834 -296.375) 
(list 1920.0844 -294.7167) 
(list 1920.0855 -293.0583) 
(list 1920.0866 -291.4) 
(list 1920.0878 -289.7417) 
(list 1920.0889 -288.0833) 
(list 1920.0901 -286.425) 
(list 1920.0914 -284.7667) 
(list 1920.0927 -283.1083) 
(list 1920.094 -281.45) 
(list 1920.0953 -279.7917) 
(list 1920.0967 -278.1333) 
(list 1920.0981 -276.475) 
(list 1920.0995 -274.8167) 
(list 1920.101 -273.1583) 
(list 1920.1025 -271.5) 
(list 1920.1041 -269.8417) 
(list 1920.1057 -268.1833) 
(list 1920.1073 -266.525) 
(list 1920.109 -264.8667) 
(list 1920.1107 -263.2083) 
(list 1920.1124 -261.55) 
(list 1920.1142 -259.8917) 
(list 1920.1161 -258.2333) 
(list 1920.1179 -256.575) 
(list 1920.1198 -254.9167) 
(list 1920.1218 -253.2583) 
(list 1920.1238 -251.6) 
(list 1920.1258 -249.9417) 
(list 1920.1279 -248.2833) 
(list 1920.13 -246.625) 
(list 1920.1321 -244.9667) 
(list 1920.1343 -243.3083) 
(list 1920.1366 -241.65) 
(list 1920.1389 -239.9917) 
(list 1920.1412 -238.3333) 
(list 1920.1436 -236.675) 
(list 1920.146 -235.0167) 
(list 1920.1485 -233.3583) 
(list 1920.151 -231.7) 
(list 1920.1536 -230.0417) 
(list 1920.1562 -228.3833) 
(list 1920.1588 -226.725) 
(list 1920.1615 -225.0667) 
(list 1920.1643 -223.4083) 
(list 1920.1671 -221.75) 
(list 1920.17 -220.0917) 
(list 1920.1729 -218.4333) 
(list 1920.1758 -216.775) 
(list 1920.1788 -215.1167) 
(list 1920.1819 -213.4583) 
(list 1920.185 -211.8) 
(list 1919.815 -211.8) 
(list 1919.8181 -213.4583) 
(list 1919.8212 -215.1167) 
(list 1919.8242 -216.775) 
(list 1919.8271 -218.4333) 
(list 1919.83 -220.0917) 
(list 1919.8329 -221.75) 
(list 1919.8357 -223.4083) 
(list 1919.8385 -225.0667) 
(list 1919.8412 -226.725) 
(list 1919.8438 -228.3833) 
(list 1919.8464 -230.0417) 
(list 1919.849 -231.7) 
(list 1919.8515 -233.3583) 
(list 1919.854 -235.0167) 
(list 1919.8564 -236.675) 
(list 1919.8588 -238.3333) 
(list 1919.8611 -239.9917) 
(list 1919.8634 -241.65) 
(list 1919.8657 -243.3083) 
(list 1919.8679 -244.9667) 
(list 1919.87 -246.625) 
(list 1919.8721 -248.2833) 
(list 1919.8742 -249.9417) 
(list 1919.8762 -251.6) 
(list 1919.8782 -253.2583) 
(list 1919.8802 -254.9167) 
(list 1919.8821 -256.575) 
(list 1919.8839 -258.2333) 
(list 1919.8858 -259.8917) 
(list 1919.8876 -261.55) 
(list 1919.8893 -263.2083) 
(list 1919.891 -264.8667) 
(list 1919.8927 -266.525) 
(list 1919.8943 -268.1833) 
(list 1919.8959 -269.8417) 
(list 1919.8975 -271.5) 
(list 1919.899 -273.1583) 
(list 1919.9005 -274.8167) 
(list 1919.9019 -276.475) 
(list 1919.9033 -278.1333) 
(list 1919.9047 -279.7917) 
(list 1919.906 -281.45) 
(list 1919.9073 -283.1083) 
(list 1919.9086 -284.7667) 
(list 1919.9099 -286.425) 
(list 1919.9111 -288.0833) 
(list 1919.9122 -289.7417) 
(list 1919.9134 -291.4) 
(list 1919.9145 -293.0583) 
(list 1919.9156 -294.7167) 
(list 1919.9166 -296.375) 
(list 1919.9177 -298.0333) 
(list 1919.9187 -299.6917) 
(list 1919.9196 -301.35) 
(list 1919.9206 -303.0083) 
(list 1919.9215 -304.6667) 
(list 1919.9223 -306.325) 
(list 1919.9232 -307.9833) 
(list 1919.924 -309.6417) 
(list 1919.9248 -311.3) 
(list 1919.9256 -312.9583) 
(list 1919.9263 -314.6167) 
(list 1919.9271 -316.275) 
(list 1919.9277 -317.9333) 
(list 1919.9284 -319.5917) 
(list 1919.9291 -321.25) 
(list 1919.9297 -322.9083) 
(list 1919.9303 -324.5667) 
(list 1919.9309 -326.225) 
(list 1919.9314 -327.8833) 
(list 1919.932 -329.5417) 
(list 1919.9325 -331.2) 
(list 1919.933 -332.8583) 
(list 1919.9334 -334.5167) 
(list 1919.9339 -336.175) 
(list 1919.9343 -337.8333) 
(list 1919.9347 -339.4917) 
(list 1919.9351 -341.15) 
(list 1919.9355 -342.8083) 
(list 1919.9359 -344.4667) 
(list 1919.9362 -346.125) 
(list 1919.9365 -347.7833) 
(list 1919.9368 -349.4417) 
(list 1919.9371 -351.1) 
(list 1919.9374 -352.7583) 
(list 1919.9376 -354.4167) 
(list 1919.9379 -356.075) 
(list 1919.9381 -357.7333) 
(list 1919.9383 -359.3917) 
(list 1919.9385 -361.05) 
(list 1919.9387 -362.7083) 
(list 1919.9389 -364.3667) 
(list 1919.9391 -366.025) 
(list 1919.9392 -367.6833) 
(list 1919.9394 -369.3417) 
(list 1919.9395 -371) 
(list 1919.9396 -372.6583) 
(list 1919.9397 -374.3167) 
(list 1919.9398 -375.975) 
(list 1919.9399 -377.6333) 
(list 1919.94 -379.2917) 
(list 1919.9401 -380.95) 
(list 1919.9401 -382.6083) 
(list 1919.9402 -384.2667) 
(list 1919.9403 -385.925) 
(list 1919.9403 -387.5833) 
(list 1919.9403 -389.2417) 
(list 1919.9404 -390.9) 
(list 1919.9404 -392.5583) 
(list 1919.9404 -394.2167) 
(list 1919.9404 -395.875) 
(list 1919.9405 -397.5333) 
(list 1919.9405 -399.1917) 
(list 1919.9405 -400.85) 
(list 1919.9405 -402.5083) 
(list 1919.9405 -404.1667) 
(list 1919.9405 -405.825) 
(list 1919.9405 -407.4833) 
(list 1919.9405 -409.1417) 
(list 1919.9405 -410.8)))
(apply 'command (append '("pline") coords '("c")))
(setq currobj (ssadd (entlast) currobj))
(command "_layer" "set" "prebias" "")
(command "_rectangle" "1919.815,-410.8" "1920.185,-211.8")
(setq currobj (ssadd (entlast) currobj))
(command "_layer" "set" "nitride" "")
(setq singlenanobeam6 currobj)
(setq currobj nil)
(setq currobj (ssadd))
; DRAWING NODE ARRAY
(setq coords (list 
(list 1920.185 -211.8) 
(list 1920.5625 -201.8) 
(list 1920.5625 -201.8) 
(list 1920.5625 -200.8) 
(list 1994.585 -212.6864) 
(list 1994.585 -207.7434) 
(list 1920.5625 -197.357) 
(list 1920.5625 -196.357) 
(list 1920.5625 -196.357) 
(list 1920.2625 -186.357) 
(list 1919.7375 -186.357) 
(list 1919.4375 -196.357) 
(list 1919.4375 -196.357) 
(list 1919.4375 -197.357) 
(list 1845.415 -207.7434) 
(list 1845.415 -212.6864) 
(list 1919.4375 -200.8) 
(list 1919.4375 -201.8) 
(list 1919.4375 -201.8) 
(list 1919.815 -211.8)))
(apply 'command (append '("pline") coords '("c")))
(setq currobj (ssadd (entlast) currobj))
(command "_layer" "set" "prebias" "")
(setq coords (list 
(list 1919.4375 -212.6864) 
(list 1919.4375 -200.8) 
(list 1845.415 -212.6864) 
(list 1845.415 -207.7434) 
(list 1919.4375 -197.357) 
(list 1919.4375 -186.357) 
(list 1920.5625 -186.357) 
(list 1920.5625 -197.357) 
(list 1994.585 -207.7434) 
(list 1994.585 -212.6864) 
(list 1920.5625 -200.8) 
(list 1920.5625 -212.6864)))
(apply 'command (append '("pline") coords '("c")))
(setq currobj (ssadd (entlast) currobj))
(command "_layer" "set" "nitride" "")
(command "_layer" "set" "fda1" "")
(setq coords (list 
(list 1920.5625 -200.657) 
(list 1994.585 -212.5434) 
(list 1994.585 -212.3664) 
(list 1920.5625 -200.58)))
(apply 'command (append '("pline") coords '("c")))
(setq currobj (ssadd (entlast) currobj))
(setq coords (list 
(list 1920.5625 -200.437) 
(list 1994.585 -212.2234) 
(list 1994.585 -212.0464) 
(list 1920.5625 -200.36)))
(apply 'command (append '("pline") coords '("c")))
(setq currobj (ssadd (entlast) currobj))
(setq coords (list 
(list 1920.5625 -200.217) 
(list 1994.585 -211.9034) 
(list 1994.585 -211.7264) 
(list 1920.5625 -200.14)))
(apply 'command (append '("pline") coords '("c")))
(setq currobj (ssadd (entlast) currobj))
(setq coords (list 
(list 1920.5625 -199.997) 
(list 1994.585 -211.5834) 
(list 1994.585 -211.4064) 
(list 1920.5625 -199.92)))
(apply 'command (append '("pline") coords '("c")))
(setq currobj (ssadd (entlast) currobj))
(setq coords (list 
(list 1920.5625 -199.777) 
(list 1994.585 -211.2634) 
(list 1994.585 -211.0864) 
(list 1920.5625 -199.7)))
(apply 'command (append '("pline") coords '("c")))
(setq currobj (ssadd (entlast) currobj))
(setq coords (list 
(list 1920.5625 -199.557) 
(list 1994.585 -210.9434) 
(list 1994.585 -210.7664) 
(list 1920.5625 -199.48)))
(apply 'command (append '("pline") coords '("c")))
(setq currobj (ssadd (entlast) currobj))
(setq coords (list 
(list 1920.5625 -199.337) 
(list 1994.585 -210.6234) 
(list 1994.585 -210.4464) 
(list 1920.5625 -199.26)))
(apply 'command (append '("pline") coords '("c")))
(setq currobj (ssadd (entlast) currobj))
(setq coords (list 
(list 1920.5625 -199.117) 
(list 1994.585 -210.3034) 
(list 1994.585 -210.1264) 
(list 1920.5625 -199.04)))
(apply 'command (append '("pline") coords '("c")))
(setq currobj (ssadd (entlast) currobj))
(setq coords (list 
(list 1920.5625 -198.897) 
(list 1994.585 -209.9834) 
(list 1994.585 -209.8064) 
(list 1920.5625 -198.82)))
(apply 'command (append '("pline") coords '("c")))
(setq currobj (ssadd (entlast) currobj))
(setq coords (list 
(list 1920.5625 -198.677) 
(list 1994.585 -209.6634) 
(list 1994.585 -209.4864) 
(list 1920.5625 -198.6)))
(apply 'command (append '("pline") coords '("c")))
(setq currobj (ssadd (entlast) currobj))
(setq coords (list 
(list 1920.5625 -198.457) 
(list 1994.585 -209.3434) 
(list 1994.585 -209.1664) 
(list 1920.5625 -198.38)))
(apply 'command (append '("pline") coords '("c")))
(setq currobj (ssadd (entlast) currobj))
(setq coords (list 
(list 1920.5625 -198.237) 
(list 1994.585 -209.0234) 
(list 1994.585 -208.8464) 
(list 1920.5625 -198.16)))
(apply 'command (append '("pline") coords '("c")))
(setq currobj (ssadd (entlast) currobj))
(setq coords (list 
(list 1920.5625 -198.017) 
(list 1994.585 -208.7034) 
(list 1994.585 -208.5264) 
(list 1920.5625 -197.94)))
(apply 'command (append '("pline") coords '("c")))
(setq currobj (ssadd (entlast) currobj))
(setq coords (list 
(list 1920.5625 -197.797) 
(list 1994.585 -208.3834) 
(list 1994.585 -208.2064) 
(list 1920.5625 -197.72)))
(apply 'command (append '("pline") coords '("c")))
(setq currobj (ssadd (entlast) currobj))
(setq coords (list 
(list 1920.5625 -197.577) 
(list 1994.585 -208.0634) 
(list 1994.585 -207.8864) 
(list 1920.5625 -197.5)))
(apply 'command (append '("pline") coords '("c")))
(setq currobj (ssadd (entlast) currobj))
(setq coords (list 
(list 1919.4375 -197.5) 
(list 1845.415 -207.8864) 
(list 1845.415 -208.0634) 
(list 1919.4375 -197.577)))
(apply 'command (append '("pline") coords '("c")))
(setq currobj (ssadd (entlast) currobj))
(setq coords (list 
(list 1919.4375 -197.72) 
(list 1845.415 -208.2064) 
(list 1845.415 -208.3834) 
(list 1919.4375 -197.797)))
(apply 'command (append '("pline") coords '("c")))
(setq currobj (ssadd (entlast) currobj))
(setq coords (list 
(list 1919.4375 -197.94) 
(list 1845.415 -208.5264) 
(list 1845.415 -208.7034) 
(list 1919.4375 -198.017)))
(apply 'command (append '("pline") coords '("c")))
(setq currobj (ssadd (entlast) currobj))
(setq coords (list 
(list 1919.4375 -198.16) 
(list 1845.415 -208.8464) 
(list 1845.415 -209.0234) 
(list 1919.4375 -198.237)))
(apply 'command (append '("pline") coords '("c")))
(setq currobj (ssadd (entlast) currobj))
(setq coords (list 
(list 1919.4375 -198.38) 
(list 1845.415 -209.1664) 
(list 1845.415 -209.3434) 
(list 1919.4375 -198.457)))
(apply 'command (append '("pline") coords '("c")))
(setq currobj (ssadd (entlast) currobj))
(setq coords (list 
(list 1919.4375 -198.6) 
(list 1845.415 -209.4864) 
(list 1845.415 -209.6634) 
(list 1919.4375 -198.677)))
(apply 'command (append '("pline") coords '("c")))
(setq currobj (ssadd (entlast) currobj))
(setq coords (list 
(list 1919.4375 -198.82) 
(list 1845.415 -209.8064) 
(list 1845.415 -209.9834) 
(list 1919.4375 -198.897)))
(apply 'command (append '("pline") coords '("c")))
(setq currobj (ssadd (entlast) currobj))
(setq coords (list 
(list 1919.4375 -199.04) 
(list 1845.415 -210.1264) 
(list 1845.415 -210.3034) 
(list 1919.4375 -199.117)))
(apply 'command (append '("pline") coords '("c")))
(setq currobj (ssadd (entlast) currobj))
(setq coords (list 
(list 1919.4375 -199.26) 
(list 1845.415 -210.4464) 
(list 1845.415 -210.6234) 
(list 1919.4375 -199.337)))
(apply 'command (append '("pline") coords '("c")))
(setq currobj (ssadd (entlast) currobj))
(setq coords (list 
(list 1919.4375 -199.48) 
(list 1845.415 -210.7664) 
(list 1845.415 -210.9434) 
(list 1919.4375 -199.557)))
(apply 'command (append '("pline") coords '("c")))
(setq currobj (ssadd (entlast) currobj))
(setq coords (list 
(list 1919.4375 -199.7) 
(list 1845.415 -211.0864) 
(list 1845.415 -211.2634) 
(list 1919.4375 -199.777)))
(apply 'command (append '("pline") coords '("c")))
(setq currobj (ssadd (entlast) currobj))
(setq coords (list 
(list 1919.4375 -199.92) 
(list 1845.415 -211.4064) 
(list 1845.415 -211.5834) 
(list 1919.4375 -199.997)))
(apply 'command (append '("pline") coords '("c")))
(setq currobj (ssadd (entlast) currobj))
(setq coords (list 
(list 1919.4375 -200.14) 
(list 1845.415 -211.7264) 
(list 1845.415 -211.9034) 
(list 1919.4375 -200.217)))
(apply 'command (append '("pline") coords '("c")))
(setq currobj (ssadd (entlast) currobj))
(setq coords (list 
(list 1919.4375 -200.36) 
(list 1845.415 -212.0464) 
(list 1845.415 -212.2234) 
(list 1919.4375 -200.437)))
(apply 'command (append '("pline") coords '("c")))
(setq currobj (ssadd (entlast) currobj))
(setq coords (list 
(list 1919.4375 -200.58) 
(list 1845.415 -212.3664) 
(list 1845.415 -212.5434) 
(list 1919.4375 -200.657)))
(apply 'command (append '("pline") coords '("c")))
(setq currobj (ssadd (entlast) currobj))
(command "_layer" "set" "nitride" "")
(command "_layer" "set" "text" "")
(command "_circle" "1918.985,-211.8" "0.075")
(command "_circle" "1918.985,-211.5" "0.075")
(command "_circle" "1918.985,-211.2" "0.075")
(command "_circle" "1918.985,-210.9" "0.075")
(command "_circle" "1918.985,-210.6" "0.075")
(command "_circle" "1918.685,-211.8" "0.075")
(command "_circle" "1918.685,-211.5" "0.075")
(command "_circle" "1918.685,-211.2" "0.075")
(command "_circle" "1918.685,-210.9" "0.075")
(command "_circle" "1918.685,-210.6" "0.075")
(command "_circle" "1918.385,-211.8" "0.075")
(command "_circle" "1918.385,-211.5" "0.075")
(command "_circle" "1918.385,-211.2" "0.075")
(command "_circle" "1918.385,-210.9" "0.075")
(command "_circle" "1918.385,-210.6" "0.075")
(command "_circle" "1918.085,-211.8" "0.075")
(command "_circle" "1918.085,-211.5" "0.075")
(command "_circle" "1918.085,-211.2" "0.075")
(command "_circle" "1918.085,-210.9" "0.075")
(command "_circle" "1918.085,-210.6" "0.075")
(command "_circle" "1917.785,-211.8" "0.075")
(command "_circle" "1917.785,-211.5" "0.075")
(command "_circle" "1917.785,-211.2" "0.075")
(command "_circle" "1917.785,-210.9" "0.075")
(command "_circle" "1917.785,-210.6" "0.075")
(command "_layer" "set" "nitride" "")
(setq anglednodearray6 currobj)
(setq currobj nil)
(setq currobj (ssadd))
; DRAWING COOLED SINGLE NANOBEAM
(setq coords (list 
(list 1920.2625 -186.357) 
(list 1920.2625 -181.357) 
(list 1919.7375 -181.357) 
(list 1919.7375 -186.357)))
(apply 'command (append '("pline") coords '("c")))
(setq currobj (ssadd (entlast) currobj))
(command "_layer" "set" "prebias" "")
(command "_rectangle" "1919.7375,-186.357" "1920.2625,-181.357")
(setq currobj (ssadd (entlast) currobj))
(command "_layer" "set" "nitride" "")
(setq coords (list 
(list 1920.2625 -181.357) 
(list 1920.5625 -171.357) 
(list 1920.5625 -171.357) 
(list 1920.5625 -170.357) 
(list 1994.585 -171.107) 
(list 1994.585 -166.164) 
(list 1920.5625 -166.914) 
(list 1920.5625 -165.914) 
(list 1920.5625 -165.914) 
(list 1920.2625 -155.914) 
(list 1919.7375 -155.914) 
(list 1919.4375 -165.914) 
(list 1919.4375 -165.914) 
(list 1919.4375 -166.914) 
(list 1845.415 -166.164) 
(list 1845.415 -171.107) 
(list 1919.4375 -170.357) 
(list 1919.4375 -171.357) 
(list 1919.4375 -171.357) 
(list 1919.7375 -181.357)))
(apply 'command (append '("pline") coords '("c")))
(setq currobj (ssadd (entlast) currobj))
(command "_layer" "set" "prebias" "")
(setq coords (list 
(list 1919.4375 -181.357) 
(list 1919.4375 -170.357) 
(list 1845.415 -171.107) 
(list 1845.415 -166.164) 
(list 1919.4375 -166.914) 
(list 1919.4375 -155.914) 
(list 1920.5625 -155.914) 
(list 1920.5625 -166.914) 
(list 1994.585 -166.164) 
(list 1994.585 -171.107) 
(list 1920.5625 -170.357) 
(list 1920.5625 -181.357)))
(apply 'command (append '("pline") coords '("c")))
(setq currobj (ssadd (entlast) currobj))
(command "_layer" "set" "nitride" "")
(command "_layer" "set" "fda1" "")
(setq coords (list 
(list 1920.5625 -170.214) 
(list 1994.585 -170.964) 
(list 1994.585 -170.787) 
(list 1920.5625 -170.137)))
(apply 'command (append '("pline") coords '("c")))
(setq currobj (ssadd (entlast) currobj))
(setq coords (list 
(list 1920.5625 -169.994) 
(list 1994.585 -170.644) 
(list 1994.585 -170.467) 
(list 1920.5625 -169.917)))
(apply 'command (append '("pline") coords '("c")))
(setq currobj (ssadd (entlast) currobj))
(setq coords (list 
(list 1920.5625 -169.774) 
(list 1994.585 -170.324) 
(list 1994.585 -170.147) 
(list 1920.5625 -169.697)))
(apply 'command (append '("pline") coords '("c")))
(setq currobj (ssadd (entlast) currobj))
(setq coords (list 
(list 1920.5625 -169.554) 
(list 1994.585 -170.004) 
(list 1994.585 -169.827) 
(list 1920.5625 -169.477)))
(apply 'command (append '("pline") coords '("c")))
(setq currobj (ssadd (entlast) currobj))
(setq coords (list 
(list 1920.5625 -169.334) 
(list 1994.585 -169.684) 
(list 1994.585 -169.507) 
(list 1920.5625 -169.257)))
(apply 'command (append '("pline") coords '("c")))
(setq currobj (ssadd (entlast) currobj))
(setq coords (list 
(list 1920.5625 -169.114) 
(list 1994.585 -169.364) 
(list 1994.585 -169.187) 
(list 1920.5625 -169.037)))
(apply 'command (append '("pline") coords '("c")))
(setq currobj (ssadd (entlast) currobj))
(setq coords (list 
(list 1920.5625 -168.894) 
(list 1994.585 -169.044) 
(list 1994.585 -168.867) 
(list 1920.5625 -168.817)))
(apply 'command (append '("pline") coords '("c")))
(setq currobj (ssadd (entlast) currobj))
(setq coords (list 
(list 1920.5625 -168.674) 
(list 1994.585 -168.724) 
(list 1994.585 -168.547) 
(list 1920.5625 -168.597)))
(apply 'command (append '("pline") coords '("c")))
(setq currobj (ssadd (entlast) currobj))
(setq coords (list 
(list 1920.5625 -168.454) 
(list 1994.585 -168.404) 
(list 1994.585 -168.227) 
(list 1920.5625 -168.377)))
(apply 'command (append '("pline") coords '("c")))
(setq currobj (ssadd (entlast) currobj))
(setq coords (list 
(list 1920.5625 -168.234) 
(list 1994.585 -168.084) 
(list 1994.585 -167.907) 
(list 1920.5625 -168.157)))
(apply 'command (append '("pline") coords '("c")))
(setq currobj (ssadd (entlast) currobj))
(setq coords (list 
(list 1920.5625 -168.014) 
(list 1994.585 -167.764) 
(list 1994.585 -167.587) 
(list 1920.5625 -167.937)))
(apply 'command (append '("pline") coords '("c")))
(setq currobj (ssadd (entlast) currobj))
(setq coords (list 
(list 1920.5625 -167.794) 
(list 1994.585 -167.444) 
(list 1994.585 -167.267) 
(list 1920.5625 -167.717)))
(apply 'command (append '("pline") coords '("c")))
(setq currobj (ssadd (entlast) currobj))
(setq coords (list 
(list 1920.5625 -167.574) 
(list 1994.585 -167.124) 
(list 1994.585 -166.947) 
(list 1920.5625 -167.497)))
(apply 'command (append '("pline") coords '("c")))
(setq currobj (ssadd (entlast) currobj))
(setq coords (list 
(list 1920.5625 -167.354) 
(list 1994.585 -166.804) 
(list 1994.585 -166.627) 
(list 1920.5625 -167.277)))
(apply 'command (append '("pline") coords '("c")))
(setq currobj (ssadd (entlast) currobj))
(setq coords (list 
(list 1920.5625 -167.134) 
(list 1994.585 -166.484) 
(list 1994.585 -166.307) 
(list 1920.5625 -167.057)))
(apply 'command (append '("pline") coords '("c")))
(setq currobj (ssadd (entlast) currobj))
(setq coords (list 
(list 1919.4375 -167.057) 
(list 1845.415 -166.307) 
(list 1845.415 -166.484) 
(list 1919.4375 -167.134)))
(apply 'command (append '("pline") coords '("c")))
(setq currobj (ssadd (entlast) currobj))
(setq coords (list 
(list 1919.4375 -167.277) 
(list 1845.415 -166.627) 
(list 1845.415 -166.804) 
(list 1919.4375 -167.354)))
(apply 'command (append '("pline") coords '("c")))
(setq currobj (ssadd (entlast) currobj))
(setq coords (list 
(list 1919.4375 -167.497) 
(list 1845.415 -166.947) 
(list 1845.415 -167.124) 
(list 1919.4375 -167.574)))
(apply 'command (append '("pline") coords '("c")))
(setq currobj (ssadd (entlast) currobj))
(setq coords (list 
(list 1919.4375 -167.717) 
(list 1845.415 -167.267) 
(list 1845.415 -167.444) 
(list 1919.4375 -167.794)))
(apply 'command (append '("pline") coords '("c")))
(setq currobj (ssadd (entlast) currobj))
(setq coords (list 
(list 1919.4375 -167.937) 
(list 1845.415 -167.587) 
(list 1845.415 -167.764) 
(list 1919.4375 -168.014)))
(apply 'command (append '("pline") coords '("c")))
(setq currobj (ssadd (entlast) currobj))
(setq coords (list 
(list 1919.4375 -168.157) 
(list 1845.415 -167.907) 
(list 1845.415 -168.084) 
(list 1919.4375 -168.234)))
(apply 'command (append '("pline") coords '("c")))
(setq currobj (ssadd (entlast) currobj))
(setq coords (list 
(list 1919.4375 -168.377) 
(list 1845.415 -168.227) 
(list 1845.415 -168.404) 
(list 1919.4375 -168.454)))
(apply 'command (append '("pline") coords '("c")))
(setq currobj (ssadd (entlast) currobj))
(setq coords (list 
(list 1919.4375 -168.597) 
(list 1845.415 -168.547) 
(list 1845.415 -168.724) 
(list 1919.4375 -168.674)))
(apply 'command (append '("pline") coords '("c")))
(setq currobj (ssadd (entlast) currobj))
(setq coords (list 
(list 1919.4375 -168.817) 
(list 1845.415 -168.867) 
(list 1845.415 -169.044) 
(list 1919.4375 -168.894)))
(apply 'command (append '("pline") coords '("c")))
(setq currobj (ssadd (entlast) currobj))
(setq coords (list 
(list 1919.4375 -169.037) 
(list 1845.415 -169.187) 
(list 1845.415 -169.364) 
(list 1919.4375 -169.114)))
(apply 'command (append '("pline") coords '("c")))
(setq currobj (ssadd (entlast) currobj))
(setq coords (list 
(list 1919.4375 -169.257) 
(list 1845.415 -169.507) 
(list 1845.415 -169.684) 
(list 1919.4375 -169.334)))
(apply 'command (append '("pline") coords '("c")))
(setq currobj (ssadd (entlast) currobj))
(setq coords (list 
(list 1919.4375 -169.477) 
(list 1845.415 -169.827) 
(list 1845.415 -170.004) 
(list 1919.4375 -169.554)))
(apply 'command (append '("pline") coords '("c")))
(setq currobj (ssadd (entlast) currobj))
(setq coords (list 
(list 1919.4375 -169.697) 
(list 1845.415 -170.147) 
(list 1845.415 -170.324) 
(list 1919.4375 -169.774)))
(apply 'command (append '("pline") coords '("c")))
(setq currobj (ssadd (entlast) currobj))
(setq coords (list 
(list 1919.4375 -169.917) 
(list 1845.415 -170.467) 
(list 1845.415 -170.644) 
(list 1919.4375 -169.994)))
(apply 'command (append '("pline") coords '("c")))
(setq currobj (ssadd (entlast) currobj))
(setq coords (list 
(list 1919.4375 -170.137) 
(list 1845.415 -170.787) 
(list 1845.415 -170.964) 
(list 1919.4375 -170.214)))
(apply 'command (append '("pline") coords '("c")))
(setq currobj (ssadd (entlast) currobj))
(command "_layer" "set" "nitride" "")
(command "_layer" "set" "text" "")
(command "_circle" "1919.0625,-181.357" "0.075")
(command "_circle" "1919.0625,-181.057" "0.075")
(command "_circle" "1919.0625,-180.757" "0.075")
(command "_circle" "1919.0625,-180.457" "0.075")
(command "_circle" "1919.0625,-180.157" "0.075")
(command "_circle" "1918.7625,-181.357" "0.075")
(command "_circle" "1918.7625,-181.057" "0.075")
(command "_circle" "1918.7625,-180.757" "0.075")
(command "_circle" "1918.7625,-180.457" "0.075")
(command "_circle" "1918.7625,-180.157" "0.075")
(command "_circle" "1918.4625,-181.357" "0.075")
(command "_circle" "1918.4625,-181.057" "0.075")
(command "_circle" "1918.4625,-180.757" "0.075")
(command "_circle" "1918.4625,-180.457" "0.075")
(command "_circle" "1918.4625,-180.157" "0.075")
(command "_circle" "1918.1625,-181.357" "0.075")
(command "_circle" "1918.1625,-181.057" "0.075")
(command "_circle" "1918.1625,-180.757" "0.075")
(command "_circle" "1918.1625,-180.457" "0.075")
(command "_circle" "1918.1625,-180.157" "0.075")
(command "_circle" "1917.8625,-181.357" "0.075")
(command "_circle" "1917.8625,-181.057" "0.075")
(command "_circle" "1917.8625,-180.757" "0.075")
(command "_circle" "1917.8625,-180.457" "0.075")
(command "_circle" "1917.8625,-180.157" "0.075")
(command "_layer" "set" "nitride" "")
(setq coords (list 
(list 1920.2625 -155.914) 
(list 1920.2625 -40.2693) 
(list 1919.7375 -40.2693) 
(list 1919.7375 -155.914)))
(apply 'command (append '("pline") coords '("c")))
(setq currobj (ssadd (entlast) currobj))
(command "_layer" "set" "prebias" "")
(command "_rectangle" "1919.7375,-155.914" "1920.2625,-40.2693")
(setq currobj (ssadd (entlast) currobj))
(command "_layer" "set" "nitride" "")
(setq coords (list 
(list 1920.2625 -40.2693) 
(list 1920.5625 -30.2693) 
(list 1920.5625 -30.2693) 
(list 1920.5625 -29.2693) 
(list 1994.585 -30.0193) 
(list 1994.585 -25.0763) 
(list 1920.5625 -25.8263) 
(list 1920.5625 -24.8263) 
(list 1920.5625 -24.8263) 
(list 1920.2625 -14.8263) 
(list 1919.7375 -14.8263) 
(list 1919.4375 -24.8263) 
(list 1919.4375 -24.8263) 
(list 1919.4375 -25.8263) 
(list 1845.415 -25.0763) 
(list 1845.415 -30.0193) 
(list 1919.4375 -29.2693) 
(list 1919.4375 -30.2693) 
(list 1919.4375 -30.2693) 
(list 1919.7375 -40.2693)))
(apply 'command (append '("pline") coords '("c")))
(setq currobj (ssadd (entlast) currobj))
(command "_layer" "set" "prebias" "")
(setq coords (list 
(list 1919.4375 -40.2693) 
(list 1919.4375 -29.2693) 
(list 1845.415 -30.0193) 
(list 1845.415 -25.0763) 
(list 1919.4375 -25.8263) 
(list 1919.4375 -14.8263) 
(list 1920.5625 -14.8263) 
(list 1920.5625 -25.8263) 
(list 1994.585 -25.0763) 
(list 1994.585 -30.0193) 
(list 1920.5625 -29.2693) 
(list 1920.5625 -40.2693)))
(apply 'command (append '("pline") coords '("c")))
(setq currobj (ssadd (entlast) currobj))
(command "_layer" "set" "nitride" "")
(command "_layer" "set" "fda1" "")
(setq coords (list 
(list 1920.5625 -29.1263) 
(list 1994.585 -29.8763) 
(list 1994.585 -29.6993) 
(list 1920.5625 -29.0493)))
(apply 'command (append '("pline") coords '("c")))
(setq currobj (ssadd (entlast) currobj))
(setq coords (list 
(list 1920.5625 -28.9063) 
(list 1994.585 -29.5563) 
(list 1994.585 -29.3793) 
(list 1920.5625 -28.8293)))
(apply 'command (append '("pline") coords '("c")))
(setq currobj (ssadd (entlast) currobj))
(setq coords (list 
(list 1920.5625 -28.6863) 
(list 1994.585 -29.2363) 
(list 1994.585 -29.0593) 
(list 1920.5625 -28.6093)))
(apply 'command (append '("pline") coords '("c")))
(setq currobj (ssadd (entlast) currobj))
(setq coords (list 
(list 1920.5625 -28.4663) 
(list 1994.585 -28.9163) 
(list 1994.585 -28.7393) 
(list 1920.5625 -28.3893)))
(apply 'command (append '("pline") coords '("c")))
(setq currobj (ssadd (entlast) currobj))
(setq coords (list 
(list 1920.5625 -28.2463) 
(list 1994.585 -28.5963) 
(list 1994.585 -28.4193) 
(list 1920.5625 -28.1693)))
(apply 'command (append '("pline") coords '("c")))
(setq currobj (ssadd (entlast) currobj))
(setq coords (list 
(list 1920.5625 -28.0263) 
(list 1994.585 -28.2763) 
(list 1994.585 -28.0993) 
(list 1920.5625 -27.9493)))
(apply 'command (append '("pline") coords '("c")))
(setq currobj (ssadd (entlast) currobj))
(setq coords (list 
(list 1920.5625 -27.8063) 
(list 1994.585 -27.9563) 
(list 1994.585 -27.7793) 
(list 1920.5625 -27.7293)))
(apply 'command (append '("pline") coords '("c")))
(setq currobj (ssadd (entlast) currobj))
(setq coords (list 
(list 1920.5625 -27.5863) 
(list 1994.585 -27.6363) 
(list 1994.585 -27.4593) 
(list 1920.5625 -27.5093)))
(apply 'command (append '("pline") coords '("c")))
(setq currobj (ssadd (entlast) currobj))
(setq coords (list 
(list 1920.5625 -27.3663) 
(list 1994.585 -27.3163) 
(list 1994.585 -27.1393) 
(list 1920.5625 -27.2893)))
(apply 'command (append '("pline") coords '("c")))
(setq currobj (ssadd (entlast) currobj))
(setq coords (list 
(list 1920.5625 -27.1463) 
(list 1994.585 -26.9963) 
(list 1994.585 -26.8193) 
(list 1920.5625 -27.0693)))
(apply 'command (append '("pline") coords '("c")))
(setq currobj (ssadd (entlast) currobj))
(setq coords (list 
(list 1920.5625 -26.9263) 
(list 1994.585 -26.6763) 
(list 1994.585 -26.4993) 
(list 1920.5625 -26.8493)))
(apply 'command (append '("pline") coords '("c")))
(setq currobj (ssadd (entlast) currobj))
(setq coords (list 
(list 1920.5625 -26.7063) 
(list 1994.585 -26.3563) 
(list 1994.585 -26.1793) 
(list 1920.5625 -26.6293)))
(apply 'command (append '("pline") coords '("c")))
(setq currobj (ssadd (entlast) currobj))
(setq coords (list 
(list 1920.5625 -26.4863) 
(list 1994.585 -26.0363) 
(list 1994.585 -25.8593) 
(list 1920.5625 -26.4093)))
(apply 'command (append '("pline") coords '("c")))
(setq currobj (ssadd (entlast) currobj))
(setq coords (list 
(list 1920.5625 -26.2663) 
(list 1994.585 -25.7163) 
(list 1994.585 -25.5393) 
(list 1920.5625 -26.1893)))
(apply 'command (append '("pline") coords '("c")))
(setq currobj (ssadd (entlast) currobj))
(setq coords (list 
(list 1920.5625 -26.0463) 
(list 1994.585 -25.3963) 
(list 1994.585 -25.2193) 
(list 1920.5625 -25.9693)))
(apply 'command (append '("pline") coords '("c")))
(setq currobj (ssadd (entlast) currobj))
(setq coords (list 
(list 1919.4375 -25.9693) 
(list 1845.415 -25.2193) 
(list 1845.415 -25.3963) 
(list 1919.4375 -26.0463)))
(apply 'command (append '("pline") coords '("c")))
(setq currobj (ssadd (entlast) currobj))
(setq coords (list 
(list 1919.4375 -26.1893) 
(list 1845.415 -25.5393) 
(list 1845.415 -25.7163) 
(list 1919.4375 -26.2663)))
(apply 'command (append '("pline") coords '("c")))
(setq currobj (ssadd (entlast) currobj))
(setq coords (list 
(list 1919.4375 -26.4093) 
(list 1845.415 -25.8593) 
(list 1845.415 -26.0363) 
(list 1919.4375 -26.4863)))
(apply 'command (append '("pline") coords '("c")))
(setq currobj (ssadd (entlast) currobj))
(setq coords (list 
(list 1919.4375 -26.6293) 
(list 1845.415 -26.1793) 
(list 1845.415 -26.3563) 
(list 1919.4375 -26.7063)))
(apply 'command (append '("pline") coords '("c")))
(setq currobj (ssadd (entlast) currobj))
(setq coords (list 
(list 1919.4375 -26.8493) 
(list 1845.415 -26.4993) 
(list 1845.415 -26.6763) 
(list 1919.4375 -26.9263)))
(apply 'command (append '("pline") coords '("c")))
(setq currobj (ssadd (entlast) currobj))
(setq coords (list 
(list 1919.4375 -27.0693) 
(list 1845.415 -26.8193) 
(list 1845.415 -26.9963) 
(list 1919.4375 -27.1463)))
(apply 'command (append '("pline") coords '("c")))
(setq currobj (ssadd (entlast) currobj))
(setq coords (list 
(list 1919.4375 -27.2893) 
(list 1845.415 -27.1393) 
(list 1845.415 -27.3163) 
(list 1919.4375 -27.3663)))
(apply 'command (append '("pline") coords '("c")))
(setq currobj (ssadd (entlast) currobj))
(setq coords (list 
(list 1919.4375 -27.5093) 
(list 1845.415 -27.4593) 
(list 1845.415 -27.6363) 
(list 1919.4375 -27.5863)))
(apply 'command (append '("pline") coords '("c")))
(setq currobj (ssadd (entlast) currobj))
(setq coords (list 
(list 1919.4375 -27.7293) 
(list 1845.415 -27.7793) 
(list 1845.415 -27.9563) 
(list 1919.4375 -27.8063)))
(apply 'command (append '("pline") coords '("c")))
(setq currobj (ssadd (entlast) currobj))
(setq coords (list 
(list 1919.4375 -27.9493) 
(list 1845.415 -28.0993) 
(list 1845.415 -28.2763) 
(list 1919.4375 -28.0263)))
(apply 'command (append '("pline") coords '("c")))
(setq currobj (ssadd (entlast) currobj))
(setq coords (list 
(list 1919.4375 -28.1693) 
(list 1845.415 -28.4193) 
(list 1845.415 -28.5963) 
(list 1919.4375 -28.2463)))
(apply 'command (append '("pline") coords '("c")))
(setq currobj (ssadd (entlast) currobj))
(setq coords (list 
(list 1919.4375 -28.3893) 
(list 1845.415 -28.7393) 
(list 1845.415 -28.9163) 
(list 1919.4375 -28.4663)))
(apply 'command (append '("pline") coords '("c")))
(setq currobj (ssadd (entlast) currobj))
(setq coords (list 
(list 1919.4375 -28.6093) 
(list 1845.415 -29.0593) 
(list 1845.415 -29.2363) 
(list 1919.4375 -28.6863)))
(apply 'command (append '("pline") coords '("c")))
(setq currobj (ssadd (entlast) currobj))
(setq coords (list 
(list 1919.4375 -28.8293) 
(list 1845.415 -29.3793) 
(list 1845.415 -29.5563) 
(list 1919.4375 -28.9063)))
(apply 'command (append '("pline") coords '("c")))
(setq currobj (ssadd (entlast) currobj))
(setq coords (list 
(list 1919.4375 -29.0493) 
(list 1845.415 -29.6993) 
(list 1845.415 -29.8763) 
(list 1919.4375 -29.1263)))
(apply 'command (append '("pline") coords '("c")))
(setq currobj (ssadd (entlast) currobj))
(command "_layer" "set" "nitride" "")
(command "_layer" "set" "text" "")
(command "_circle" "1919.0625,-40.2693" "0.075")
(command "_circle" "1919.0625,-39.9693" "0.075")
(command "_circle" "1919.0625,-39.6693" "0.075")
(command "_circle" "1919.0625,-39.3693" "0.075")
(command "_circle" "1919.0625,-39.0693" "0.075")
(command "_circle" "1918.7625,-40.2693" "0.075")
(command "_circle" "1918.7625,-39.9693" "0.075")
(command "_circle" "1918.7625,-39.6693" "0.075")
(command "_circle" "1918.7625,-39.3693" "0.075")
(command "_circle" "1918.7625,-39.0693" "0.075")
(command "_circle" "1918.4625,-40.2693" "0.075")
(command "_circle" "1918.4625,-39.9693" "0.075")
(command "_circle" "1918.4625,-39.6693" "0.075")
(command "_circle" "1918.4625,-39.3693" "0.075")
(command "_circle" "1918.4625,-39.0693" "0.075")
(command "_circle" "1918.1625,-40.2693" "0.075")
(command "_circle" "1918.1625,-39.9693" "0.075")
(command "_circle" "1918.1625,-39.6693" "0.075")
(command "_circle" "1918.1625,-39.3693" "0.075")
(command "_circle" "1918.1625,-39.0693" "0.075")
(command "_circle" "1917.8625,-40.2693" "0.075")
(command "_circle" "1917.8625,-39.9693" "0.075")
(command "_circle" "1917.8625,-39.6693" "0.075")
(command "_circle" "1917.8625,-39.3693" "0.075")
(command "_circle" "1917.8625,-39.0693" "0.075")
(command "_layer" "set" "nitride" "")
(setq coords (list 
(list 1920.2625 -14.8263) 
(list 1920.2625 100.8184) 
(list 1919.7375 100.8184) 
(list 1919.7375 -14.8263)))
(apply 'command (append '("pline") coords '("c")))
(setq currobj (ssadd (entlast) currobj))
(command "_layer" "set" "prebias" "")
(command "_rectangle" "1919.7375,-14.8263" "1920.2625,100.8184")
(setq currobj (ssadd (entlast) currobj))
(command "_layer" "set" "nitride" "")
(setq coords (list 
(list 1920.2625 100.8184) 
(list 1920.5625 110.8184) 
(list 1920.5625 110.8184) 
(list 1920.5625 111.8184) 
(list 1994.585 111.0684) 
(list 1994.585 116.0114) 
(list 1920.5625 115.2614) 
(list 1920.5625 116.2614) 
(list 1920.5625 116.2614) 
(list 1920.2625 126.2614) 
(list 1919.7375 126.2614) 
(list 1919.4375 116.2614) 
(list 1919.4375 116.2614) 
(list 1919.4375 115.2614) 
(list 1845.415 116.0114) 
(list 1845.415 111.0684) 
(list 1919.4375 111.8184) 
(list 1919.4375 110.8184) 
(list 1919.4375 110.8184) 
(list 1919.7375 100.8184)))
(apply 'command (append '("pline") coords '("c")))
(setq currobj (ssadd (entlast) currobj))
(command "_layer" "set" "prebias" "")
(setq coords (list 
(list 1919.4375 100.8184) 
(list 1919.4375 111.8184) 
(list 1845.415 111.0684) 
(list 1845.415 116.0114) 
(list 1919.4375 115.2614) 
(list 1919.4375 126.2614) 
(list 1920.5625 126.2614) 
(list 1920.5625 115.2614) 
(list 1994.585 116.0114) 
(list 1994.585 111.0684) 
(list 1920.5625 111.8184) 
(list 1920.5625 100.8184)))
(apply 'command (append '("pline") coords '("c")))
(setq currobj (ssadd (entlast) currobj))
(command "_layer" "set" "nitride" "")
(command "_layer" "set" "fda1" "")
(setq coords (list 
(list 1920.5625 111.9614) 
(list 1994.585 111.2114) 
(list 1994.585 111.3884) 
(list 1920.5625 112.0384)))
(apply 'command (append '("pline") coords '("c")))
(setq currobj (ssadd (entlast) currobj))
(setq coords (list 
(list 1920.5625 112.1814) 
(list 1994.585 111.5314) 
(list 1994.585 111.7084) 
(list 1920.5625 112.2584)))
(apply 'command (append '("pline") coords '("c")))
(setq currobj (ssadd (entlast) currobj))
(setq coords (list 
(list 1920.5625 112.4014) 
(list 1994.585 111.8514) 
(list 1994.585 112.0284) 
(list 1920.5625 112.4784)))
(apply 'command (append '("pline") coords '("c")))
(setq currobj (ssadd (entlast) currobj))
(setq coords (list 
(list 1920.5625 112.6214) 
(list 1994.585 112.1714) 
(list 1994.585 112.3484) 
(list 1920.5625 112.6984)))
(apply 'command (append '("pline") coords '("c")))
(setq currobj (ssadd (entlast) currobj))
(setq coords (list 
(list 1920.5625 112.8414) 
(list 1994.585 112.4914) 
(list 1994.585 112.6684) 
(list 1920.5625 112.9184)))
(apply 'command (append '("pline") coords '("c")))
(setq currobj (ssadd (entlast) currobj))
(setq coords (list 
(list 1920.5625 113.0614) 
(list 1994.585 112.8114) 
(list 1994.585 112.9884) 
(list 1920.5625 113.1384)))
(apply 'command (append '("pline") coords '("c")))
(setq currobj (ssadd (entlast) currobj))
(setq coords (list 
(list 1920.5625 113.2814) 
(list 1994.585 113.1314) 
(list 1994.585 113.3084) 
(list 1920.5625 113.3584)))
(apply 'command (append '("pline") coords '("c")))
(setq currobj (ssadd (entlast) currobj))
(setq coords (list 
(list 1920.5625 113.5014) 
(list 1994.585 113.4514) 
(list 1994.585 113.6284) 
(list 1920.5625 113.5784)))
(apply 'command (append '("pline") coords '("c")))
(setq currobj (ssadd (entlast) currobj))
(setq coords (list 
(list 1920.5625 113.7214) 
(list 1994.585 113.7714) 
(list 1994.585 113.9484) 
(list 1920.5625 113.7984)))
(apply 'command (append '("pline") coords '("c")))
(setq currobj (ssadd (entlast) currobj))
(setq coords (list 
(list 1920.5625 113.9414) 
(list 1994.585 114.0914) 
(list 1994.585 114.2684) 
(list 1920.5625 114.0184)))
(apply 'command (append '("pline") coords '("c")))
(setq currobj (ssadd (entlast) currobj))
(setq coords (list 
(list 1920.5625 114.1614) 
(list 1994.585 114.4114) 
(list 1994.585 114.5884) 
(list 1920.5625 114.2384)))
(apply 'command (append '("pline") coords '("c")))
(setq currobj (ssadd (entlast) currobj))
(setq coords (list 
(list 1920.5625 114.3814) 
(list 1994.585 114.7314) 
(list 1994.585 114.9084) 
(list 1920.5625 114.4584)))
(apply 'command (append '("pline") coords '("c")))
(setq currobj (ssadd (entlast) currobj))
(setq coords (list 
(list 1920.5625 114.6014) 
(list 1994.585 115.0514) 
(list 1994.585 115.2284) 
(list 1920.5625 114.6784)))
(apply 'command (append '("pline") coords '("c")))
(setq currobj (ssadd (entlast) currobj))
(setq coords (list 
(list 1920.5625 114.8214) 
(list 1994.585 115.3714) 
(list 1994.585 115.5484) 
(list 1920.5625 114.8984)))
(apply 'command (append '("pline") coords '("c")))
(setq currobj (ssadd (entlast) currobj))
(setq coords (list 
(list 1920.5625 115.0414) 
(list 1994.585 115.6914) 
(list 1994.585 115.8684) 
(list 1920.5625 115.1184)))
(apply 'command (append '("pline") coords '("c")))
(setq currobj (ssadd (entlast) currobj))
(setq coords (list 
(list 1919.4375 115.1184) 
(list 1845.415 115.8684) 
(list 1845.415 115.6914) 
(list 1919.4375 115.0414)))
(apply 'command (append '("pline") coords '("c")))
(setq currobj (ssadd (entlast) currobj))
(setq coords (list 
(list 1919.4375 114.8984) 
(list 1845.415 115.5484) 
(list 1845.415 115.3714) 
(list 1919.4375 114.8214)))
(apply 'command (append '("pline") coords '("c")))
(setq currobj (ssadd (entlast) currobj))
(setq coords (list 
(list 1919.4375 114.6784) 
(list 1845.415 115.2284) 
(list 1845.415 115.0514) 
(list 1919.4375 114.6014)))
(apply 'command (append '("pline") coords '("c")))
(setq currobj (ssadd (entlast) currobj))
(setq coords (list 
(list 1919.4375 114.4584) 
(list 1845.415 114.9084) 
(list 1845.415 114.7314) 
(list 1919.4375 114.3814)))
(apply 'command (append '("pline") coords '("c")))
(setq currobj (ssadd (entlast) currobj))
(setq coords (list 
(list 1919.4375 114.2384) 
(list 1845.415 114.5884) 
(list 1845.415 114.4114) 
(list 1919.4375 114.1614)))
(apply 'command (append '("pline") coords '("c")))
(setq currobj (ssadd (entlast) currobj))
(setq coords (list 
(list 1919.4375 114.0184) 
(list 1845.415 114.2684) 
(list 1845.415 114.0914) 
(list 1919.4375 113.9414)))
(apply 'command (append '("pline") coords '("c")))
(setq currobj (ssadd (entlast) currobj))
(setq coords (list 
(list 1919.4375 113.7984) 
(list 1845.415 113.9484) 
(list 1845.415 113.7714) 
(list 1919.4375 113.7214)))
(apply 'command (append '("pline") coords '("c")))
(setq currobj (ssadd (entlast) currobj))
(setq coords (list 
(list 1919.4375 113.5784) 
(list 1845.415 113.6284) 
(list 1845.415 113.4514) 
(list 1919.4375 113.5014)))
(apply 'command (append '("pline") coords '("c")))
(setq currobj (ssadd (entlast) currobj))
(setq coords (list 
(list 1919.4375 113.3584) 
(list 1845.415 113.3084) 
(list 1845.415 113.1314) 
(list 1919.4375 113.2814)))
(apply 'command (append '("pline") coords '("c")))
(setq currobj (ssadd (entlast) currobj))
(setq coords (list 
(list 1919.4375 113.1384) 
(list 1845.415 112.9884) 
(list 1845.415 112.8114) 
(list 1919.4375 113.0614)))
(apply 'command (append '("pline") coords '("c")))
(setq currobj (ssadd (entlast) currobj))
(setq coords (list 
(list 1919.4375 112.9184) 
(list 1845.415 112.6684) 
(list 1845.415 112.4914) 
(list 1919.4375 112.8414)))
(apply 'command (append '("pline") coords '("c")))
(setq currobj (ssadd (entlast) currobj))
(setq coords (list 
(list 1919.4375 112.6984) 
(list 1845.415 112.3484) 
(list 1845.415 112.1714) 
(list 1919.4375 112.6214)))
(apply 'command (append '("pline") coords '("c")))
(setq currobj (ssadd (entlast) currobj))
(setq coords (list 
(list 1919.4375 112.4784) 
(list 1845.415 112.0284) 
(list 1845.415 111.8514) 
(list 1919.4375 112.4014)))
(apply 'command (append '("pline") coords '("c")))
(setq currobj (ssadd (entlast) currobj))
(setq coords (list 
(list 1919.4375 112.2584) 
(list 1845.415 111.7084) 
(list 1845.415 111.5314) 
(list 1919.4375 112.1814)))
(apply 'command (append '("pline") coords '("c")))
(setq currobj (ssadd (entlast) currobj))
(setq coords (list 
(list 1919.4375 112.0384) 
(list 1845.415 111.3884) 
(list 1845.415 111.2114) 
(list 1919.4375 111.9614)))
(apply 'command (append '("pline") coords '("c")))
(setq currobj (ssadd (entlast) currobj))
(command "_layer" "set" "nitride" "")
(command "_layer" "set" "text" "")
(command "_circle" "1919.0625,100.8184" "0.075")
(command "_circle" "1919.0625,101.1184" "0.075")
(command "_circle" "1919.0625,101.4184" "0.075")
(command "_circle" "1919.0625,101.7184" "0.075")
(command "_circle" "1919.0625,102.0184" "0.075")
(command "_circle" "1918.7625,100.8184" "0.075")
(command "_circle" "1918.7625,101.1184" "0.075")
(command "_circle" "1918.7625,101.4184" "0.075")
(command "_circle" "1918.7625,101.7184" "0.075")
(command "_circle" "1918.7625,102.0184" "0.075")
(command "_circle" "1918.4625,100.8184" "0.075")
(command "_circle" "1918.4625,101.1184" "0.075")
(command "_circle" "1918.4625,101.4184" "0.075")
(command "_circle" "1918.4625,101.7184" "0.075")
(command "_circle" "1918.4625,102.0184" "0.075")
(command "_circle" "1918.1625,100.8184" "0.075")
(command "_circle" "1918.1625,101.1184" "0.075")
(command "_circle" "1918.1625,101.4184" "0.075")
(command "_circle" "1918.1625,101.7184" "0.075")
(command "_circle" "1918.1625,102.0184" "0.075")
(command "_circle" "1917.8625,100.8184" "0.075")
(command "_circle" "1917.8625,101.1184" "0.075")
(command "_circle" "1917.8625,101.4184" "0.075")
(command "_circle" "1917.8625,101.7184" "0.075")
(command "_circle" "1917.8625,102.0184" "0.075")
(command "_layer" "set" "nitride" "")
(setq coords (list 
(list 1920.2625 126.2614) 
(list 1920.2625 241.9061) 
(list 1919.7375 241.9061) 
(list 1919.7375 126.2614)))
(apply 'command (append '("pline") coords '("c")))
(setq currobj (ssadd (entlast) currobj))
(command "_layer" "set" "prebias" "")
(command "_rectangle" "1919.7375,126.2614" "1920.2625,241.9061")
(setq currobj (ssadd (entlast) currobj))
(command "_layer" "set" "nitride" "")
(setq coords (list 
(list 1920.2625 241.9061) 
(list 1920.5625 251.9061) 
(list 1920.5625 251.9061) 
(list 1920.5625 252.9061) 
(list 1994.585 252.1561) 
(list 1994.585 257.0991) 
(list 1920.5625 256.3491) 
(list 1920.5625 257.3491) 
(list 1920.5625 257.3491) 
(list 1920.2625 267.3491) 
(list 1919.7375 267.3491) 
(list 1919.4375 257.3491) 
(list 1919.4375 257.3491) 
(list 1919.4375 256.3491) 
(list 1845.415 257.0991) 
(list 1845.415 252.1561) 
(list 1919.4375 252.9061) 
(list 1919.4375 251.9061) 
(list 1919.4375 251.9061) 
(list 1919.7375 241.9061)))
(apply 'command (append '("pline") coords '("c")))
(setq currobj (ssadd (entlast) currobj))
(command "_layer" "set" "prebias" "")
(setq coords (list 
(list 1919.4375 241.9061) 
(list 1919.4375 252.9061) 
(list 1845.415 252.1561) 
(list 1845.415 257.0991) 
(list 1919.4375 256.3491) 
(list 1919.4375 267.3491) 
(list 1920.5625 267.3491) 
(list 1920.5625 256.3491) 
(list 1994.585 257.0991) 
(list 1994.585 252.1561) 
(list 1920.5625 252.9061) 
(list 1920.5625 241.9061)))
(apply 'command (append '("pline") coords '("c")))
(setq currobj (ssadd (entlast) currobj))
(command "_layer" "set" "nitride" "")
(command "_layer" "set" "fda1" "")
(setq coords (list 
(list 1920.5625 253.0491) 
(list 1994.585 252.2991) 
(list 1994.585 252.4761) 
(list 1920.5625 253.1261)))
(apply 'command (append '("pline") coords '("c")))
(setq currobj (ssadd (entlast) currobj))
(setq coords (list 
(list 1920.5625 253.2691) 
(list 1994.585 252.6191) 
(list 1994.585 252.7961) 
(list 1920.5625 253.3461)))
(apply 'command (append '("pline") coords '("c")))
(setq currobj (ssadd (entlast) currobj))
(setq coords (list 
(list 1920.5625 253.4891) 
(list 1994.585 252.9391) 
(list 1994.585 253.1161) 
(list 1920.5625 253.5661)))
(apply 'command (append '("pline") coords '("c")))
(setq currobj (ssadd (entlast) currobj))
(setq coords (list 
(list 1920.5625 253.7091) 
(list 1994.585 253.2591) 
(list 1994.585 253.4361) 
(list 1920.5625 253.7861)))
(apply 'command (append '("pline") coords '("c")))
(setq currobj (ssadd (entlast) currobj))
(setq coords (list 
(list 1920.5625 253.9291) 
(list 1994.585 253.5791) 
(list 1994.585 253.7561) 
(list 1920.5625 254.0061)))
(apply 'command (append '("pline") coords '("c")))
(setq currobj (ssadd (entlast) currobj))
(setq coords (list 
(list 1920.5625 254.1491) 
(list 1994.585 253.8991) 
(list 1994.585 254.0761) 
(list 1920.5625 254.2261)))
(apply 'command (append '("pline") coords '("c")))
(setq currobj (ssadd (entlast) currobj))
(setq coords (list 
(list 1920.5625 254.3691) 
(list 1994.585 254.2191) 
(list 1994.585 254.3961) 
(list 1920.5625 254.4461)))
(apply 'command (append '("pline") coords '("c")))
(setq currobj (ssadd (entlast) currobj))
(setq coords (list 
(list 1920.5625 254.5891) 
(list 1994.585 254.5391) 
(list 1994.585 254.7161) 
(list 1920.5625 254.6661)))
(apply 'command (append '("pline") coords '("c")))
(setq currobj (ssadd (entlast) currobj))
(setq coords (list 
(list 1920.5625 254.8091) 
(list 1994.585 254.8591) 
(list 1994.585 255.0361) 
(list 1920.5625 254.8861)))
(apply 'command (append '("pline") coords '("c")))
(setq currobj (ssadd (entlast) currobj))
(setq coords (list 
(list 1920.5625 255.0291) 
(list 1994.585 255.1791) 
(list 1994.585 255.3561) 
(list 1920.5625 255.1061)))
(apply 'command (append '("pline") coords '("c")))
(setq currobj (ssadd (entlast) currobj))
(setq coords (list 
(list 1920.5625 255.2491) 
(list 1994.585 255.4991) 
(list 1994.585 255.6761) 
(list 1920.5625 255.3261)))
(apply 'command (append '("pline") coords '("c")))
(setq currobj (ssadd (entlast) currobj))
(setq coords (list 
(list 1920.5625 255.4691) 
(list 1994.585 255.8191) 
(list 1994.585 255.9961) 
(list 1920.5625 255.5461)))
(apply 'command (append '("pline") coords '("c")))
(setq currobj (ssadd (entlast) currobj))
(setq coords (list 
(list 1920.5625 255.6891) 
(list 1994.585 256.1391) 
(list 1994.585 256.3161) 
(list 1920.5625 255.7661)))
(apply 'command (append '("pline") coords '("c")))
(setq currobj (ssadd (entlast) currobj))
(setq coords (list 
(list 1920.5625 255.9091) 
(list 1994.585 256.4591) 
(list 1994.585 256.6361) 
(list 1920.5625 255.9861)))
(apply 'command (append '("pline") coords '("c")))
(setq currobj (ssadd (entlast) currobj))
(setq coords (list 
(list 1920.5625 256.1291) 
(list 1994.585 256.7791) 
(list 1994.585 256.9561) 
(list 1920.5625 256.2061)))
(apply 'command (append '("pline") coords '("c")))
(setq currobj (ssadd (entlast) currobj))
(setq coords (list 
(list 1919.4375 256.2061) 
(list 1845.415 256.9561) 
(list 1845.415 256.7791) 
(list 1919.4375 256.1291)))
(apply 'command (append '("pline") coords '("c")))
(setq currobj (ssadd (entlast) currobj))
(setq coords (list 
(list 1919.4375 255.9861) 
(list 1845.415 256.6361) 
(list 1845.415 256.4591) 
(list 1919.4375 255.9091)))
(apply 'command (append '("pline") coords '("c")))
(setq currobj (ssadd (entlast) currobj))
(setq coords (list 
(list 1919.4375 255.7661) 
(list 1845.415 256.3161) 
(list 1845.415 256.1391) 
(list 1919.4375 255.6891)))
(apply 'command (append '("pline") coords '("c")))
(setq currobj (ssadd (entlast) currobj))
(setq coords (list 
(list 1919.4375 255.5461) 
(list 1845.415 255.9961) 
(list 1845.415 255.8191) 
(list 1919.4375 255.4691)))
(apply 'command (append '("pline") coords '("c")))
(setq currobj (ssadd (entlast) currobj))
(setq coords (list 
(list 1919.4375 255.3261) 
(list 1845.415 255.6761) 
(list 1845.415 255.4991) 
(list 1919.4375 255.2491)))
(apply 'command (append '("pline") coords '("c")))
(setq currobj (ssadd (entlast) currobj))
(setq coords (list 
(list 1919.4375 255.1061) 
(list 1845.415 255.3561) 
(list 1845.415 255.1791) 
(list 1919.4375 255.0291)))
(apply 'command (append '("pline") coords '("c")))
(setq currobj (ssadd (entlast) currobj))
(setq coords (list 
(list 1919.4375 254.8861) 
(list 1845.415 255.0361) 
(list 1845.415 254.8591) 
(list 1919.4375 254.8091)))
(apply 'command (append '("pline") coords '("c")))
(setq currobj (ssadd (entlast) currobj))
(setq coords (list 
(list 1919.4375 254.6661) 
(list 1845.415 254.7161) 
(list 1845.415 254.5391) 
(list 1919.4375 254.5891)))
(apply 'command (append '("pline") coords '("c")))
(setq currobj (ssadd (entlast) currobj))
(setq coords (list 
(list 1919.4375 254.4461) 
(list 1845.415 254.3961) 
(list 1845.415 254.2191) 
(list 1919.4375 254.3691)))
(apply 'command (append '("pline") coords '("c")))
(setq currobj (ssadd (entlast) currobj))
(setq coords (list 
(list 1919.4375 254.2261) 
(list 1845.415 254.0761) 
(list 1845.415 253.8991) 
(list 1919.4375 254.1491)))
(apply 'command (append '("pline") coords '("c")))
(setq currobj (ssadd (entlast) currobj))
(setq coords (list 
(list 1919.4375 254.0061) 
(list 1845.415 253.7561) 
(list 1845.415 253.5791) 
(list 1919.4375 253.9291)))
(apply 'command (append '("pline") coords '("c")))
(setq currobj (ssadd (entlast) currobj))
(setq coords (list 
(list 1919.4375 253.7861) 
(list 1845.415 253.4361) 
(list 1845.415 253.2591) 
(list 1919.4375 253.7091)))
(apply 'command (append '("pline") coords '("c")))
(setq currobj (ssadd (entlast) currobj))
(setq coords (list 
(list 1919.4375 253.5661) 
(list 1845.415 253.1161) 
(list 1845.415 252.9391) 
(list 1919.4375 253.4891)))
(apply 'command (append '("pline") coords '("c")))
(setq currobj (ssadd (entlast) currobj))
(setq coords (list 
(list 1919.4375 253.3461) 
(list 1845.415 252.7961) 
(list 1845.415 252.6191) 
(list 1919.4375 253.2691)))
(apply 'command (append '("pline") coords '("c")))
(setq currobj (ssadd (entlast) currobj))
(setq coords (list 
(list 1919.4375 253.1261) 
(list 1845.415 252.4761) 
(list 1845.415 252.2991) 
(list 1919.4375 253.0491)))
(apply 'command (append '("pline") coords '("c")))
(setq currobj (ssadd (entlast) currobj))
(command "_layer" "set" "nitride" "")
(command "_layer" "set" "text" "")
(command "_circle" "1919.0625,241.9061" "0.075")
(command "_circle" "1919.0625,242.2061" "0.075")
(command "_circle" "1919.0625,242.5061" "0.075")
(command "_circle" "1919.0625,242.8061" "0.075")
(command "_circle" "1919.0625,243.1061" "0.075")
(command "_circle" "1918.7625,241.9061" "0.075")
(command "_circle" "1918.7625,242.2061" "0.075")
(command "_circle" "1918.7625,242.5061" "0.075")
(command "_circle" "1918.7625,242.8061" "0.075")
(command "_circle" "1918.7625,243.1061" "0.075")
(command "_circle" "1918.4625,241.9061" "0.075")
(command "_circle" "1918.4625,242.2061" "0.075")
(command "_circle" "1918.4625,242.5061" "0.075")
(command "_circle" "1918.4625,242.8061" "0.075")
(command "_circle" "1918.4625,243.1061" "0.075")
(command "_circle" "1918.1625,241.9061" "0.075")
(command "_circle" "1918.1625,242.2061" "0.075")
(command "_circle" "1918.1625,242.5061" "0.075")
(command "_circle" "1918.1625,242.8061" "0.075")
(command "_circle" "1918.1625,243.1061" "0.075")
(command "_circle" "1917.8625,241.9061" "0.075")
(command "_circle" "1917.8625,242.2061" "0.075")
(command "_circle" "1917.8625,242.5061" "0.075")
(command "_circle" "1917.8625,242.8061" "0.075")
(command "_circle" "1917.8625,243.1061" "0.075")
(command "_layer" "set" "nitride" "")
(setq coords (list 
(list 1920.2625 267.3491) 
(list 1920.2625 382.9939) 
(list 1919.7375 382.9939) 
(list 1919.7375 267.3491)))
(apply 'command (append '("pline") coords '("c")))
(setq currobj (ssadd (entlast) currobj))
(command "_layer" "set" "prebias" "")
(command "_rectangle" "1919.7375,267.3491" "1920.2625,382.9939")
(setq currobj (ssadd (entlast) currobj))
(command "_layer" "set" "nitride" "")
(setq coords (list 
(list 1920.2625 382.9939) 
(list 1920.5625 392.9939) 
(list 1920.5625 392.9939) 
(list 1920.5625 393.9939) 
(list 1994.585 393.2439) 
(list 1994.585 398.1869) 
(list 1920.5625 397.4369) 
(list 1920.5625 398.4369) 
(list 1920.5625 398.4369) 
(list 1920.2625 408.4369) 
(list 1919.7375 408.4369) 
(list 1919.4375 398.4369) 
(list 1919.4375 398.4369) 
(list 1919.4375 397.4369) 
(list 1845.415 398.1869) 
(list 1845.415 393.2439) 
(list 1919.4375 393.9939) 
(list 1919.4375 392.9939) 
(list 1919.4375 392.9939) 
(list 1919.7375 382.9939)))
(apply 'command (append '("pline") coords '("c")))
(setq currobj (ssadd (entlast) currobj))
(command "_layer" "set" "prebias" "")
(setq coords (list 
(list 1919.4375 382.9939) 
(list 1919.4375 393.9939) 
(list 1845.415 393.2439) 
(list 1845.415 398.1869) 
(list 1919.4375 397.4369) 
(list 1919.4375 408.4369) 
(list 1920.5625 408.4369) 
(list 1920.5625 397.4369) 
(list 1994.585 398.1869) 
(list 1994.585 393.2439) 
(list 1920.5625 393.9939) 
(list 1920.5625 382.9939)))
(apply 'command (append '("pline") coords '("c")))
(setq currobj (ssadd (entlast) currobj))
(command "_layer" "set" "nitride" "")
(command "_layer" "set" "fda1" "")
(setq coords (list 
(list 1920.5625 394.1369) 
(list 1994.585 393.3869) 
(list 1994.585 393.5639) 
(list 1920.5625 394.2139)))
(apply 'command (append '("pline") coords '("c")))
(setq currobj (ssadd (entlast) currobj))
(setq coords (list 
(list 1920.5625 394.3569) 
(list 1994.585 393.7069) 
(list 1994.585 393.8839) 
(list 1920.5625 394.4339)))
(apply 'command (append '("pline") coords '("c")))
(setq currobj (ssadd (entlast) currobj))
(setq coords (list 
(list 1920.5625 394.5769) 
(list 1994.585 394.0269) 
(list 1994.585 394.2039) 
(list 1920.5625 394.6539)))
(apply 'command (append '("pline") coords '("c")))
(setq currobj (ssadd (entlast) currobj))
(setq coords (list 
(list 1920.5625 394.7969) 
(list 1994.585 394.3469) 
(list 1994.585 394.5239) 
(list 1920.5625 394.8739)))
(apply 'command (append '("pline") coords '("c")))
(setq currobj (ssadd (entlast) currobj))
(setq coords (list 
(list 1920.5625 395.0169) 
(list 1994.585 394.6669) 
(list 1994.585 394.8439) 
(list 1920.5625 395.0939)))
(apply 'command (append '("pline") coords '("c")))
(setq currobj (ssadd (entlast) currobj))
(setq coords (list 
(list 1920.5625 395.2369) 
(list 1994.585 394.9869) 
(list 1994.585 395.1639) 
(list 1920.5625 395.3139)))
(apply 'command (append '("pline") coords '("c")))
(setq currobj (ssadd (entlast) currobj))
(setq coords (list 
(list 1920.5625 395.4569) 
(list 1994.585 395.3069) 
(list 1994.585 395.4839) 
(list 1920.5625 395.5339)))
(apply 'command (append '("pline") coords '("c")))
(setq currobj (ssadd (entlast) currobj))
(setq coords (list 
(list 1920.5625 395.6769) 
(list 1994.585 395.6269) 
(list 1994.585 395.8039) 
(list 1920.5625 395.7539)))
(apply 'command (append '("pline") coords '("c")))
(setq currobj (ssadd (entlast) currobj))
(setq coords (list 
(list 1920.5625 395.8969) 
(list 1994.585 395.9469) 
(list 1994.585 396.1239) 
(list 1920.5625 395.9739)))
(apply 'command (append '("pline") coords '("c")))
(setq currobj (ssadd (entlast) currobj))
(setq coords (list 
(list 1920.5625 396.1169) 
(list 1994.585 396.2669) 
(list 1994.585 396.4439) 
(list 1920.5625 396.1939)))
(apply 'command (append '("pline") coords '("c")))
(setq currobj (ssadd (entlast) currobj))
(setq coords (list 
(list 1920.5625 396.3369) 
(list 1994.585 396.5869) 
(list 1994.585 396.7639) 
(list 1920.5625 396.4139)))
(apply 'command (append '("pline") coords '("c")))
(setq currobj (ssadd (entlast) currobj))
(setq coords (list 
(list 1920.5625 396.5569) 
(list 1994.585 396.9069) 
(list 1994.585 397.0839) 
(list 1920.5625 396.6339)))
(apply 'command (append '("pline") coords '("c")))
(setq currobj (ssadd (entlast) currobj))
(setq coords (list 
(list 1920.5625 396.7769) 
(list 1994.585 397.2269) 
(list 1994.585 397.4039) 
(list 1920.5625 396.8539)))
(apply 'command (append '("pline") coords '("c")))
(setq currobj (ssadd (entlast) currobj))
(setq coords (list 
(list 1920.5625 396.9969) 
(list 1994.585 397.5469) 
(list 1994.585 397.7239) 
(list 1920.5625 397.0739)))
(apply 'command (append '("pline") coords '("c")))
(setq currobj (ssadd (entlast) currobj))
(setq coords (list 
(list 1920.5625 397.2169) 
(list 1994.585 397.8669) 
(list 1994.585 398.0439) 
(list 1920.5625 397.2939)))
(apply 'command (append '("pline") coords '("c")))
(setq currobj (ssadd (entlast) currobj))
(setq coords (list 
(list 1919.4375 397.2939) 
(list 1845.415 398.0439) 
(list 1845.415 397.8669) 
(list 1919.4375 397.2169)))
(apply 'command (append '("pline") coords '("c")))
(setq currobj (ssadd (entlast) currobj))
(setq coords (list 
(list 1919.4375 397.0739) 
(list 1845.415 397.7239) 
(list 1845.415 397.5469) 
(list 1919.4375 396.9969)))
(apply 'command (append '("pline") coords '("c")))
(setq currobj (ssadd (entlast) currobj))
(setq coords (list 
(list 1919.4375 396.8539) 
(list 1845.415 397.4039) 
(list 1845.415 397.2269) 
(list 1919.4375 396.7769)))
(apply 'command (append '("pline") coords '("c")))
(setq currobj (ssadd (entlast) currobj))
(setq coords (list 
(list 1919.4375 396.6339) 
(list 1845.415 397.0839) 
(list 1845.415 396.9069) 
(list 1919.4375 396.5569)))
(apply 'command (append '("pline") coords '("c")))
(setq currobj (ssadd (entlast) currobj))
(setq coords (list 
(list 1919.4375 396.4139) 
(list 1845.415 396.7639) 
(list 1845.415 396.5869) 
(list 1919.4375 396.3369)))
(apply 'command (append '("pline") coords '("c")))
(setq currobj (ssadd (entlast) currobj))
(setq coords (list 
(list 1919.4375 396.1939) 
(list 1845.415 396.4439) 
(list 1845.415 396.2669) 
(list 1919.4375 396.1169)))
(apply 'command (append '("pline") coords '("c")))
(setq currobj (ssadd (entlast) currobj))
(setq coords (list 
(list 1919.4375 395.9739) 
(list 1845.415 396.1239) 
(list 1845.415 395.9469) 
(list 1919.4375 395.8969)))
(apply 'command (append '("pline") coords '("c")))
(setq currobj (ssadd (entlast) currobj))
(setq coords (list 
(list 1919.4375 395.7539) 
(list 1845.415 395.8039) 
(list 1845.415 395.6269) 
(list 1919.4375 395.6769)))
(apply 'command (append '("pline") coords '("c")))
(setq currobj (ssadd (entlast) currobj))
(setq coords (list 
(list 1919.4375 395.5339) 
(list 1845.415 395.4839) 
(list 1845.415 395.3069) 
(list 1919.4375 395.4569)))
(apply 'command (append '("pline") coords '("c")))
(setq currobj (ssadd (entlast) currobj))
(setq coords (list 
(list 1919.4375 395.3139) 
(list 1845.415 395.1639) 
(list 1845.415 394.9869) 
(list 1919.4375 395.2369)))
(apply 'command (append '("pline") coords '("c")))
(setq currobj (ssadd (entlast) currobj))
(setq coords (list 
(list 1919.4375 395.0939) 
(list 1845.415 394.8439) 
(list 1845.415 394.6669) 
(list 1919.4375 395.0169)))
(apply 'command (append '("pline") coords '("c")))
(setq currobj (ssadd (entlast) currobj))
(setq coords (list 
(list 1919.4375 394.8739) 
(list 1845.415 394.5239) 
(list 1845.415 394.3469) 
(list 1919.4375 394.7969)))
(apply 'command (append '("pline") coords '("c")))
(setq currobj (ssadd (entlast) currobj))
(setq coords (list 
(list 1919.4375 394.6539) 
(list 1845.415 394.2039) 
(list 1845.415 394.0269) 
(list 1919.4375 394.5769)))
(apply 'command (append '("pline") coords '("c")))
(setq currobj (ssadd (entlast) currobj))
(setq coords (list 
(list 1919.4375 394.4339) 
(list 1845.415 393.8839) 
(list 1845.415 393.7069) 
(list 1919.4375 394.3569)))
(apply 'command (append '("pline") coords '("c")))
(setq currobj (ssadd (entlast) currobj))
(setq coords (list 
(list 1919.4375 394.2139) 
(list 1845.415 393.5639) 
(list 1845.415 393.3869) 
(list 1919.4375 394.1369)))
(apply 'command (append '("pline") coords '("c")))
(setq currobj (ssadd (entlast) currobj))
(command "_layer" "set" "nitride" "")
(command "_layer" "set" "text" "")
(command "_circle" "1919.0625,382.9939" "0.075")
(command "_circle" "1919.0625,383.2939" "0.075")
(command "_circle" "1919.0625,383.5939" "0.075")
(command "_circle" "1919.0625,383.8939" "0.075")
(command "_circle" "1919.0625,384.1939" "0.075")
(command "_circle" "1918.7625,382.9939" "0.075")
(command "_circle" "1918.7625,383.2939" "0.075")
(command "_circle" "1918.7625,383.5939" "0.075")
(command "_circle" "1918.7625,383.8939" "0.075")
(command "_circle" "1918.7625,384.1939" "0.075")
(command "_circle" "1918.4625,382.9939" "0.075")
(command "_circle" "1918.4625,383.2939" "0.075")
(command "_circle" "1918.4625,383.5939" "0.075")
(command "_circle" "1918.4625,383.8939" "0.075")
(command "_circle" "1918.4625,384.1939" "0.075")
(command "_circle" "1918.1625,382.9939" "0.075")
(command "_circle" "1918.1625,383.2939" "0.075")
(command "_circle" "1918.1625,383.5939" "0.075")
(command "_circle" "1918.1625,383.8939" "0.075")
(command "_circle" "1918.1625,384.1939" "0.075")
(command "_circle" "1917.8625,382.9939" "0.075")
(command "_circle" "1917.8625,383.2939" "0.075")
(command "_circle" "1917.8625,383.5939" "0.075")
(command "_circle" "1917.8625,383.8939" "0.075")
(command "_circle" "1917.8625,384.1939" "0.075")
(command "_layer" "set" "nitride" "")
(setq coords (list 
(list 1920.2625 408.4369) 
(list 1920.2625 524.0816) 
(list 1919.7375 524.0816) 
(list 1919.7375 408.4369)))
(apply 'command (append '("pline") coords '("c")))
(setq currobj (ssadd (entlast) currobj))
(command "_layer" "set" "prebias" "")
(command "_rectangle" "1919.7375,408.4369" "1920.2625,524.0816")
(setq currobj (ssadd (entlast) currobj))
(command "_layer" "set" "nitride" "")
(setq coords (list 
(list 1920.2625 524.0816) 
(list 1920.5625 534.0816) 
(list 1920.5625 534.0816) 
(list 1920.5625 535.0816) 
(list 1994.585 534.3316) 
(list 1994.585 539.2746) 
(list 1920.5625 538.5246) 
(list 1920.5625 539.5246) 
(list 1920.5625 539.5246) 
(list 1920.2625 549.5246) 
(list 1919.7375 549.5246) 
(list 1919.4375 539.5246) 
(list 1919.4375 539.5246) 
(list 1919.4375 538.5246) 
(list 1845.415 539.2746) 
(list 1845.415 534.3316) 
(list 1919.4375 535.0816) 
(list 1919.4375 534.0816) 
(list 1919.4375 534.0816) 
(list 1919.7375 524.0816)))
(apply 'command (append '("pline") coords '("c")))
(setq currobj (ssadd (entlast) currobj))
(command "_layer" "set" "prebias" "")
(setq coords (list 
(list 1919.4375 524.0816) 
(list 1919.4375 535.0816) 
(list 1845.415 534.3316) 
(list 1845.415 539.2746) 
(list 1919.4375 538.5246) 
(list 1919.4375 549.5246) 
(list 1920.5625 549.5246) 
(list 1920.5625 538.5246) 
(list 1994.585 539.2746) 
(list 1994.585 534.3316) 
(list 1920.5625 535.0816) 
(list 1920.5625 524.0816)))
(apply 'command (append '("pline") coords '("c")))
(setq currobj (ssadd (entlast) currobj))
(command "_layer" "set" "nitride" "")
(command "_layer" "set" "fda1" "")
(setq coords (list 
(list 1920.5625 535.2246) 
(list 1994.585 534.4746) 
(list 1994.585 534.6516) 
(list 1920.5625 535.3016)))
(apply 'command (append '("pline") coords '("c")))
(setq currobj (ssadd (entlast) currobj))
(setq coords (list 
(list 1920.5625 535.4446) 
(list 1994.585 534.7946) 
(list 1994.585 534.9716) 
(list 1920.5625 535.5216)))
(apply 'command (append '("pline") coords '("c")))
(setq currobj (ssadd (entlast) currobj))
(setq coords (list 
(list 1920.5625 535.6646) 
(list 1994.585 535.1146) 
(list 1994.585 535.2916) 
(list 1920.5625 535.7416)))
(apply 'command (append '("pline") coords '("c")))
(setq currobj (ssadd (entlast) currobj))
(setq coords (list 
(list 1920.5625 535.8846) 
(list 1994.585 535.4346) 
(list 1994.585 535.6116) 
(list 1920.5625 535.9616)))
(apply 'command (append '("pline") coords '("c")))
(setq currobj (ssadd (entlast) currobj))
(setq coords (list 
(list 1920.5625 536.1046) 
(list 1994.585 535.7546) 
(list 1994.585 535.9316) 
(list 1920.5625 536.1816)))
(apply 'command (append '("pline") coords '("c")))
(setq currobj (ssadd (entlast) currobj))
(setq coords (list 
(list 1920.5625 536.3246) 
(list 1994.585 536.0746) 
(list 1994.585 536.2516) 
(list 1920.5625 536.4016)))
(apply 'command (append '("pline") coords '("c")))
(setq currobj (ssadd (entlast) currobj))
(setq coords (list 
(list 1920.5625 536.5446) 
(list 1994.585 536.3946) 
(list 1994.585 536.5716) 
(list 1920.5625 536.6216)))
(apply 'command (append '("pline") coords '("c")))
(setq currobj (ssadd (entlast) currobj))
(setq coords (list 
(list 1920.5625 536.7646) 
(list 1994.585 536.7146) 
(list 1994.585 536.8916) 
(list 1920.5625 536.8416)))
(apply 'command (append '("pline") coords '("c")))
(setq currobj (ssadd (entlast) currobj))
(setq coords (list 
(list 1920.5625 536.9846) 
(list 1994.585 537.0346) 
(list 1994.585 537.2116) 
(list 1920.5625 537.0616)))
(apply 'command (append '("pline") coords '("c")))
(setq currobj (ssadd (entlast) currobj))
(setq coords (list 
(list 1920.5625 537.2046) 
(list 1994.585 537.3546) 
(list 1994.585 537.5316) 
(list 1920.5625 537.2816)))
(apply 'command (append '("pline") coords '("c")))
(setq currobj (ssadd (entlast) currobj))
(setq coords (list 
(list 1920.5625 537.4246) 
(list 1994.585 537.6746) 
(list 1994.585 537.8516) 
(list 1920.5625 537.5016)))
(apply 'command (append '("pline") coords '("c")))
(setq currobj (ssadd (entlast) currobj))
(setq coords (list 
(list 1920.5625 537.6446) 
(list 1994.585 537.9946) 
(list 1994.585 538.1716) 
(list 1920.5625 537.7216)))
(apply 'command (append '("pline") coords '("c")))
(setq currobj (ssadd (entlast) currobj))
(setq coords (list 
(list 1920.5625 537.8646) 
(list 1994.585 538.3146) 
(list 1994.585 538.4916) 
(list 1920.5625 537.9416)))
(apply 'command (append '("pline") coords '("c")))
(setq currobj (ssadd (entlast) currobj))
(setq coords (list 
(list 1920.5625 538.0846) 
(list 1994.585 538.6346) 
(list 1994.585 538.8116) 
(list 1920.5625 538.1616)))
(apply 'command (append '("pline") coords '("c")))
(setq currobj (ssadd (entlast) currobj))
(setq coords (list 
(list 1920.5625 538.3046) 
(list 1994.585 538.9546) 
(list 1994.585 539.1316) 
(list 1920.5625 538.3816)))
(apply 'command (append '("pline") coords '("c")))
(setq currobj (ssadd (entlast) currobj))
(setq coords (list 
(list 1919.4375 538.3816) 
(list 1845.415 539.1316) 
(list 1845.415 538.9546) 
(list 1919.4375 538.3046)))
(apply 'command (append '("pline") coords '("c")))
(setq currobj (ssadd (entlast) currobj))
(setq coords (list 
(list 1919.4375 538.1616) 
(list 1845.415 538.8116) 
(list 1845.415 538.6346) 
(list 1919.4375 538.0846)))
(apply 'command (append '("pline") coords '("c")))
(setq currobj (ssadd (entlast) currobj))
(setq coords (list 
(list 1919.4375 537.9416) 
(list 1845.415 538.4916) 
(list 1845.415 538.3146) 
(list 1919.4375 537.8646)))
(apply 'command (append '("pline") coords '("c")))
(setq currobj (ssadd (entlast) currobj))
(setq coords (list 
(list 1919.4375 537.7216) 
(list 1845.415 538.1716) 
(list 1845.415 537.9946) 
(list 1919.4375 537.6446)))
(apply 'command (append '("pline") coords '("c")))
(setq currobj (ssadd (entlast) currobj))
(setq coords (list 
(list 1919.4375 537.5016) 
(list 1845.415 537.8516) 
(list 1845.415 537.6746) 
(list 1919.4375 537.4246)))
(apply 'command (append '("pline") coords '("c")))
(setq currobj (ssadd (entlast) currobj))
(setq coords (list 
(list 1919.4375 537.2816) 
(list 1845.415 537.5316) 
(list 1845.415 537.3546) 
(list 1919.4375 537.2046)))
(apply 'command (append '("pline") coords '("c")))
(setq currobj (ssadd (entlast) currobj))
(setq coords (list 
(list 1919.4375 537.0616) 
(list 1845.415 537.2116) 
(list 1845.415 537.0346) 
(list 1919.4375 536.9846)))
(apply 'command (append '("pline") coords '("c")))
(setq currobj (ssadd (entlast) currobj))
(setq coords (list 
(list 1919.4375 536.8416) 
(list 1845.415 536.8916) 
(list 1845.415 536.7146) 
(list 1919.4375 536.7646)))
(apply 'command (append '("pline") coords '("c")))
(setq currobj (ssadd (entlast) currobj))
(setq coords (list 
(list 1919.4375 536.6216) 
(list 1845.415 536.5716) 
(list 1845.415 536.3946) 
(list 1919.4375 536.5446)))
(apply 'command (append '("pline") coords '("c")))
(setq currobj (ssadd (entlast) currobj))
(setq coords (list 
(list 1919.4375 536.4016) 
(list 1845.415 536.2516) 
(list 1845.415 536.0746) 
(list 1919.4375 536.3246)))
(apply 'command (append '("pline") coords '("c")))
(setq currobj (ssadd (entlast) currobj))
(setq coords (list 
(list 1919.4375 536.1816) 
(list 1845.415 535.9316) 
(list 1845.415 535.7546) 
(list 1919.4375 536.1046)))
(apply 'command (append '("pline") coords '("c")))
(setq currobj (ssadd (entlast) currobj))
(setq coords (list 
(list 1919.4375 535.9616) 
(list 1845.415 535.6116) 
(list 1845.415 535.4346) 
(list 1919.4375 535.8846)))
(apply 'command (append '("pline") coords '("c")))
(setq currobj (ssadd (entlast) currobj))
(setq coords (list 
(list 1919.4375 535.7416) 
(list 1845.415 535.2916) 
(list 1845.415 535.1146) 
(list 1919.4375 535.6646)))
(apply 'command (append '("pline") coords '("c")))
(setq currobj (ssadd (entlast) currobj))
(setq coords (list 
(list 1919.4375 535.5216) 
(list 1845.415 534.9716) 
(list 1845.415 534.7946) 
(list 1919.4375 535.4446)))
(apply 'command (append '("pline") coords '("c")))
(setq currobj (ssadd (entlast) currobj))
(setq coords (list 
(list 1919.4375 535.3016) 
(list 1845.415 534.6516) 
(list 1845.415 534.4746) 
(list 1919.4375 535.2246)))
(apply 'command (append '("pline") coords '("c")))
(setq currobj (ssadd (entlast) currobj))
(command "_layer" "set" "nitride" "")
(command "_layer" "set" "text" "")
(command "_circle" "1919.0625,524.0816" "0.075")
(command "_circle" "1919.0625,524.3816" "0.075")
(command "_circle" "1919.0625,524.6816" "0.075")
(command "_circle" "1919.0625,524.9816" "0.075")
(command "_circle" "1919.0625,525.2816" "0.075")
(command "_circle" "1918.7625,524.0816" "0.075")
(command "_circle" "1918.7625,524.3816" "0.075")
(command "_circle" "1918.7625,524.6816" "0.075")
(command "_circle" "1918.7625,524.9816" "0.075")
(command "_circle" "1918.7625,525.2816" "0.075")
(command "_circle" "1918.4625,524.0816" "0.075")
(command "_circle" "1918.4625,524.3816" "0.075")
(command "_circle" "1918.4625,524.6816" "0.075")
(command "_circle" "1918.4625,524.9816" "0.075")
(command "_circle" "1918.4625,525.2816" "0.075")
(command "_circle" "1918.1625,524.0816" "0.075")
(command "_circle" "1918.1625,524.3816" "0.075")
(command "_circle" "1918.1625,524.6816" "0.075")
(command "_circle" "1918.1625,524.9816" "0.075")
(command "_circle" "1918.1625,525.2816" "0.075")
(command "_circle" "1917.8625,524.0816" "0.075")
(command "_circle" "1917.8625,524.3816" "0.075")
(command "_circle" "1917.8625,524.6816" "0.075")
(command "_circle" "1917.8625,524.9816" "0.075")
(command "_circle" "1917.8625,525.2816" "0.075")
(command "_layer" "set" "nitride" "")
(setq coords (list 
(list 1920.2625 549.5246) 
(list 1920.2625 665.1693) 
(list 1919.7375 665.1693) 
(list 1919.7375 549.5246)))
(apply 'command (append '("pline") coords '("c")))
(setq currobj (ssadd (entlast) currobj))
(command "_layer" "set" "prebias" "")
(command "_rectangle" "1919.7375,549.5246" "1920.2625,665.1693")
(setq currobj (ssadd (entlast) currobj))
(command "_layer" "set" "nitride" "")
(setq coords (list 
(list 1920.2625 665.1693) 
(list 1920.5625 675.1693) 
(list 1920.5625 675.1693) 
(list 1920.5625 676.1693) 
(list 1994.585 675.4193) 
(list 1994.585 680.3623) 
(list 1920.5625 679.6123) 
(list 1920.5625 680.6123) 
(list 1920.5625 680.6123) 
(list 1920.2625 690.6123) 
(list 1919.7375 690.6123) 
(list 1919.4375 680.6123) 
(list 1919.4375 680.6123) 
(list 1919.4375 679.6123) 
(list 1845.415 680.3623) 
(list 1845.415 675.4193) 
(list 1919.4375 676.1693) 
(list 1919.4375 675.1693) 
(list 1919.4375 675.1693) 
(list 1919.7375 665.1693)))
(apply 'command (append '("pline") coords '("c")))
(setq currobj (ssadd (entlast) currobj))
(command "_layer" "set" "prebias" "")
(setq coords (list 
(list 1919.4375 665.1693) 
(list 1919.4375 676.1693) 
(list 1845.415 675.4193) 
(list 1845.415 680.3623) 
(list 1919.4375 679.6123) 
(list 1919.4375 690.6123) 
(list 1920.5625 690.6123) 
(list 1920.5625 679.6123) 
(list 1994.585 680.3623) 
(list 1994.585 675.4193) 
(list 1920.5625 676.1693) 
(list 1920.5625 665.1693)))
(apply 'command (append '("pline") coords '("c")))
(setq currobj (ssadd (entlast) currobj))
(command "_layer" "set" "nitride" "")
(command "_layer" "set" "fda1" "")
(setq coords (list 
(list 1920.5625 676.3123) 
(list 1994.585 675.5623) 
(list 1994.585 675.7393) 
(list 1920.5625 676.3893)))
(apply 'command (append '("pline") coords '("c")))
(setq currobj (ssadd (entlast) currobj))
(setq coords (list 
(list 1920.5625 676.5323) 
(list 1994.585 675.8823) 
(list 1994.585 676.0593) 
(list 1920.5625 676.6093)))
(apply 'command (append '("pline") coords '("c")))
(setq currobj (ssadd (entlast) currobj))
(setq coords (list 
(list 1920.5625 676.7523) 
(list 1994.585 676.2023) 
(list 1994.585 676.3793) 
(list 1920.5625 676.8293)))
(apply 'command (append '("pline") coords '("c")))
(setq currobj (ssadd (entlast) currobj))
(setq coords (list 
(list 1920.5625 676.9723) 
(list 1994.585 676.5223) 
(list 1994.585 676.6993) 
(list 1920.5625 677.0493)))
(apply 'command (append '("pline") coords '("c")))
(setq currobj (ssadd (entlast) currobj))
(setq coords (list 
(list 1920.5625 677.1923) 
(list 1994.585 676.8423) 
(list 1994.585 677.0193) 
(list 1920.5625 677.2693)))
(apply 'command (append '("pline") coords '("c")))
(setq currobj (ssadd (entlast) currobj))
(setq coords (list 
(list 1920.5625 677.4123) 
(list 1994.585 677.1623) 
(list 1994.585 677.3393) 
(list 1920.5625 677.4893)))
(apply 'command (append '("pline") coords '("c")))
(setq currobj (ssadd (entlast) currobj))
(setq coords (list 
(list 1920.5625 677.6323) 
(list 1994.585 677.4823) 
(list 1994.585 677.6593) 
(list 1920.5625 677.7093)))
(apply 'command (append '("pline") coords '("c")))
(setq currobj (ssadd (entlast) currobj))
(setq coords (list 
(list 1920.5625 677.8523) 
(list 1994.585 677.8023) 
(list 1994.585 677.9793) 
(list 1920.5625 677.9293)))
(apply 'command (append '("pline") coords '("c")))
(setq currobj (ssadd (entlast) currobj))
(setq coords (list 
(list 1920.5625 678.0723) 
(list 1994.585 678.1223) 
(list 1994.585 678.2993) 
(list 1920.5625 678.1493)))
(apply 'command (append '("pline") coords '("c")))
(setq currobj (ssadd (entlast) currobj))
(setq coords (list 
(list 1920.5625 678.2923) 
(list 1994.585 678.4423) 
(list 1994.585 678.6193) 
(list 1920.5625 678.3693)))
(apply 'command (append '("pline") coords '("c")))
(setq currobj (ssadd (entlast) currobj))
(setq coords (list 
(list 1920.5625 678.5123) 
(list 1994.585 678.7623) 
(list 1994.585 678.9393) 
(list 1920.5625 678.5893)))
(apply 'command (append '("pline") coords '("c")))
(setq currobj (ssadd (entlast) currobj))
(setq coords (list 
(list 1920.5625 678.7323) 
(list 1994.585 679.0823) 
(list 1994.585 679.2593) 
(list 1920.5625 678.8093)))
(apply 'command (append '("pline") coords '("c")))
(setq currobj (ssadd (entlast) currobj))
(setq coords (list 
(list 1920.5625 678.9523) 
(list 1994.585 679.4023) 
(list 1994.585 679.5793) 
(list 1920.5625 679.0293)))
(apply 'command (append '("pline") coords '("c")))
(setq currobj (ssadd (entlast) currobj))
(setq coords (list 
(list 1920.5625 679.1723) 
(list 1994.585 679.7223) 
(list 1994.585 679.8993) 
(list 1920.5625 679.2493)))
(apply 'command (append '("pline") coords '("c")))
(setq currobj (ssadd (entlast) currobj))
(setq coords (list 
(list 1920.5625 679.3923) 
(list 1994.585 680.0423) 
(list 1994.585 680.2193) 
(list 1920.5625 679.4693)))
(apply 'command (append '("pline") coords '("c")))
(setq currobj (ssadd (entlast) currobj))
(setq coords (list 
(list 1919.4375 679.4693) 
(list 1845.415 680.2193) 
(list 1845.415 680.0423) 
(list 1919.4375 679.3923)))
(apply 'command (append '("pline") coords '("c")))
(setq currobj (ssadd (entlast) currobj))
(setq coords (list 
(list 1919.4375 679.2493) 
(list 1845.415 679.8993) 
(list 1845.415 679.7223) 
(list 1919.4375 679.1723)))
(apply 'command (append '("pline") coords '("c")))
(setq currobj (ssadd (entlast) currobj))
(setq coords (list 
(list 1919.4375 679.0293) 
(list 1845.415 679.5793) 
(list 1845.415 679.4023) 
(list 1919.4375 678.9523)))
(apply 'command (append '("pline") coords '("c")))
(setq currobj (ssadd (entlast) currobj))
(setq coords (list 
(list 1919.4375 678.8093) 
(list 1845.415 679.2593) 
(list 1845.415 679.0823) 
(list 1919.4375 678.7323)))
(apply 'command (append '("pline") coords '("c")))
(setq currobj (ssadd (entlast) currobj))
(setq coords (list 
(list 1919.4375 678.5893) 
(list 1845.415 678.9393) 
(list 1845.415 678.7623) 
(list 1919.4375 678.5123)))
(apply 'command (append '("pline") coords '("c")))
(setq currobj (ssadd (entlast) currobj))
(setq coords (list 
(list 1919.4375 678.3693) 
(list 1845.415 678.6193) 
(list 1845.415 678.4423) 
(list 1919.4375 678.2923)))
(apply 'command (append '("pline") coords '("c")))
(setq currobj (ssadd (entlast) currobj))
(setq coords (list 
(list 1919.4375 678.1493) 
(list 1845.415 678.2993) 
(list 1845.415 678.1223) 
(list 1919.4375 678.0723)))
(apply 'command (append '("pline") coords '("c")))
(setq currobj (ssadd (entlast) currobj))
(setq coords (list 
(list 1919.4375 677.9293) 
(list 1845.415 677.9793) 
(list 1845.415 677.8023) 
(list 1919.4375 677.8523)))
(apply 'command (append '("pline") coords '("c")))
(setq currobj (ssadd (entlast) currobj))
(setq coords (list 
(list 1919.4375 677.7093) 
(list 1845.415 677.6593) 
(list 1845.415 677.4823) 
(list 1919.4375 677.6323)))
(apply 'command (append '("pline") coords '("c")))
(setq currobj (ssadd (entlast) currobj))
(setq coords (list 
(list 1919.4375 677.4893) 
(list 1845.415 677.3393) 
(list 1845.415 677.1623) 
(list 1919.4375 677.4123)))
(apply 'command (append '("pline") coords '("c")))
(setq currobj (ssadd (entlast) currobj))
(setq coords (list 
(list 1919.4375 677.2693) 
(list 1845.415 677.0193) 
(list 1845.415 676.8423) 
(list 1919.4375 677.1923)))
(apply 'command (append '("pline") coords '("c")))
(setq currobj (ssadd (entlast) currobj))
(setq coords (list 
(list 1919.4375 677.0493) 
(list 1845.415 676.6993) 
(list 1845.415 676.5223) 
(list 1919.4375 676.9723)))
(apply 'command (append '("pline") coords '("c")))
(setq currobj (ssadd (entlast) currobj))
(setq coords (list 
(list 1919.4375 676.8293) 
(list 1845.415 676.3793) 
(list 1845.415 676.2023) 
(list 1919.4375 676.7523)))
(apply 'command (append '("pline") coords '("c")))
(setq currobj (ssadd (entlast) currobj))
(setq coords (list 
(list 1919.4375 676.6093) 
(list 1845.415 676.0593) 
(list 1845.415 675.8823) 
(list 1919.4375 676.5323)))
(apply 'command (append '("pline") coords '("c")))
(setq currobj (ssadd (entlast) currobj))
(setq coords (list 
(list 1919.4375 676.3893) 
(list 1845.415 675.7393) 
(list 1845.415 675.5623) 
(list 1919.4375 676.3123)))
(apply 'command (append '("pline") coords '("c")))
(setq currobj (ssadd (entlast) currobj))
(command "_layer" "set" "nitride" "")
(command "_layer" "set" "text" "")
(command "_circle" "1919.0625,665.1693" "0.075")
(command "_circle" "1919.0625,665.4693" "0.075")
(command "_circle" "1919.0625,665.7693" "0.075")
(command "_circle" "1919.0625,666.0693" "0.075")
(command "_circle" "1919.0625,666.3693" "0.075")
(command "_circle" "1918.7625,665.1693" "0.075")
(command "_circle" "1918.7625,665.4693" "0.075")
(command "_circle" "1918.7625,665.7693" "0.075")
(command "_circle" "1918.7625,666.0693" "0.075")
(command "_circle" "1918.7625,666.3693" "0.075")
(command "_circle" "1918.4625,665.1693" "0.075")
(command "_circle" "1918.4625,665.4693" "0.075")
(command "_circle" "1918.4625,665.7693" "0.075")
(command "_circle" "1918.4625,666.0693" "0.075")
(command "_circle" "1918.4625,666.3693" "0.075")
(command "_circle" "1918.1625,665.1693" "0.075")
(command "_circle" "1918.1625,665.4693" "0.075")
(command "_circle" "1918.1625,665.7693" "0.075")
(command "_circle" "1918.1625,666.0693" "0.075")
(command "_circle" "1918.1625,666.3693" "0.075")
(command "_circle" "1917.8625,665.1693" "0.075")
(command "_circle" "1917.8625,665.4693" "0.075")
(command "_circle" "1917.8625,665.7693" "0.075")
(command "_circle" "1917.8625,666.0693" "0.075")
(command "_circle" "1917.8625,666.3693" "0.075")
(command "_layer" "set" "nitride" "")
(setq coords (list 
(list 1920.2625 690.6123) 
(list 1920.2625 806.257) 
(list 1919.7375 806.257) 
(list 1919.7375 690.6123)))
(apply 'command (append '("pline") coords '("c")))
(setq currobj (ssadd (entlast) currobj))
(command "_layer" "set" "prebias" "")
(command "_rectangle" "1919.7375,690.6123" "1920.2625,806.257")
(setq currobj (ssadd (entlast) currobj))
(command "_layer" "set" "nitride" "")
(setq coords (list 
(list 1920.2625 806.257) 
(list 1920.5625 816.257) 
(list 1920.5625 816.257) 
(list 1920.5625 817.257) 
(list 1994.585 816.507) 
(list 1994.585 821.45) 
(list 1920.5625 820.7) 
(list 1920.5625 821.7) 
(list 1920.5625 821.7) 
(list 1920.2625 831.7) 
(list 1919.7375 831.7) 
(list 1919.4375 821.7) 
(list 1919.4375 821.7) 
(list 1919.4375 820.7) 
(list 1845.415 821.45) 
(list 1845.415 816.507) 
(list 1919.4375 817.257) 
(list 1919.4375 816.257) 
(list 1919.4375 816.257) 
(list 1919.7375 806.257)))
(apply 'command (append '("pline") coords '("c")))
(setq currobj (ssadd (entlast) currobj))
(command "_layer" "set" "prebias" "")
(setq coords (list 
(list 1919.4375 806.257) 
(list 1919.4375 817.257) 
(list 1845.415 816.507) 
(list 1845.415 821.45) 
(list 1919.4375 820.7) 
(list 1919.4375 831.7) 
(list 1920.5625 831.7) 
(list 1920.5625 820.7) 
(list 1994.585 821.45) 
(list 1994.585 816.507) 
(list 1920.5625 817.257) 
(list 1920.5625 806.257)))
(apply 'command (append '("pline") coords '("c")))
(setq currobj (ssadd (entlast) currobj))
(command "_layer" "set" "nitride" "")
(command "_layer" "set" "fda1" "")
(setq coords (list 
(list 1920.5625 817.4) 
(list 1994.585 816.65) 
(list 1994.585 816.827) 
(list 1920.5625 817.477)))
(apply 'command (append '("pline") coords '("c")))
(setq currobj (ssadd (entlast) currobj))
(setq coords (list 
(list 1920.5625 817.62) 
(list 1994.585 816.97) 
(list 1994.585 817.147) 
(list 1920.5625 817.697)))
(apply 'command (append '("pline") coords '("c")))
(setq currobj (ssadd (entlast) currobj))
(setq coords (list 
(list 1920.5625 817.84) 
(list 1994.585 817.29) 
(list 1994.585 817.467) 
(list 1920.5625 817.917)))
(apply 'command (append '("pline") coords '("c")))
(setq currobj (ssadd (entlast) currobj))
(setq coords (list 
(list 1920.5625 818.06) 
(list 1994.585 817.61) 
(list 1994.585 817.787) 
(list 1920.5625 818.137)))
(apply 'command (append '("pline") coords '("c")))
(setq currobj (ssadd (entlast) currobj))
(setq coords (list 
(list 1920.5625 818.28) 
(list 1994.585 817.93) 
(list 1994.585 818.107) 
(list 1920.5625 818.357)))
(apply 'command (append '("pline") coords '("c")))
(setq currobj (ssadd (entlast) currobj))
(setq coords (list 
(list 1920.5625 818.5) 
(list 1994.585 818.25) 
(list 1994.585 818.427) 
(list 1920.5625 818.577)))
(apply 'command (append '("pline") coords '("c")))
(setq currobj (ssadd (entlast) currobj))
(setq coords (list 
(list 1920.5625 818.72) 
(list 1994.585 818.57) 
(list 1994.585 818.747) 
(list 1920.5625 818.797)))
(apply 'command (append '("pline") coords '("c")))
(setq currobj (ssadd (entlast) currobj))
(setq coords (list 
(list 1920.5625 818.94) 
(list 1994.585 818.89) 
(list 1994.585 819.067) 
(list 1920.5625 819.017)))
(apply 'command (append '("pline") coords '("c")))
(setq currobj (ssadd (entlast) currobj))
(setq coords (list 
(list 1920.5625 819.16) 
(list 1994.585 819.21) 
(list 1994.585 819.387) 
(list 1920.5625 819.237)))
(apply 'command (append '("pline") coords '("c")))
(setq currobj (ssadd (entlast) currobj))
(setq coords (list 
(list 1920.5625 819.38) 
(list 1994.585 819.53) 
(list 1994.585 819.707) 
(list 1920.5625 819.457)))
(apply 'command (append '("pline") coords '("c")))
(setq currobj (ssadd (entlast) currobj))
(setq coords (list 
(list 1920.5625 819.6) 
(list 1994.585 819.85) 
(list 1994.585 820.027) 
(list 1920.5625 819.677)))
(apply 'command (append '("pline") coords '("c")))
(setq currobj (ssadd (entlast) currobj))
(setq coords (list 
(list 1920.5625 819.82) 
(list 1994.585 820.17) 
(list 1994.585 820.347) 
(list 1920.5625 819.897)))
(apply 'command (append '("pline") coords '("c")))
(setq currobj (ssadd (entlast) currobj))
(setq coords (list 
(list 1920.5625 820.04) 
(list 1994.585 820.49) 
(list 1994.585 820.667) 
(list 1920.5625 820.117)))
(apply 'command (append '("pline") coords '("c")))
(setq currobj (ssadd (entlast) currobj))
(setq coords (list 
(list 1920.5625 820.26) 
(list 1994.585 820.81) 
(list 1994.585 820.987) 
(list 1920.5625 820.337)))
(apply 'command (append '("pline") coords '("c")))
(setq currobj (ssadd (entlast) currobj))
(setq coords (list 
(list 1920.5625 820.48) 
(list 1994.585 821.13) 
(list 1994.585 821.307) 
(list 1920.5625 820.557)))
(apply 'command (append '("pline") coords '("c")))
(setq currobj (ssadd (entlast) currobj))
(setq coords (list 
(list 1919.4375 820.557) 
(list 1845.415 821.307) 
(list 1845.415 821.13) 
(list 1919.4375 820.48)))
(apply 'command (append '("pline") coords '("c")))
(setq currobj (ssadd (entlast) currobj))
(setq coords (list 
(list 1919.4375 820.337) 
(list 1845.415 820.987) 
(list 1845.415 820.81) 
(list 1919.4375 820.26)))
(apply 'command (append '("pline") coords '("c")))
(setq currobj (ssadd (entlast) currobj))
(setq coords (list 
(list 1919.4375 820.117) 
(list 1845.415 820.667) 
(list 1845.415 820.49) 
(list 1919.4375 820.04)))
(apply 'command (append '("pline") coords '("c")))
(setq currobj (ssadd (entlast) currobj))
(setq coords (list 
(list 1919.4375 819.897) 
(list 1845.415 820.347) 
(list 1845.415 820.17) 
(list 1919.4375 819.82)))
(apply 'command (append '("pline") coords '("c")))
(setq currobj (ssadd (entlast) currobj))
(setq coords (list 
(list 1919.4375 819.677) 
(list 1845.415 820.027) 
(list 1845.415 819.85) 
(list 1919.4375 819.6)))
(apply 'command (append '("pline") coords '("c")))
(setq currobj (ssadd (entlast) currobj))
(setq coords (list 
(list 1919.4375 819.457) 
(list 1845.415 819.707) 
(list 1845.415 819.53) 
(list 1919.4375 819.38)))
(apply 'command (append '("pline") coords '("c")))
(setq currobj (ssadd (entlast) currobj))
(setq coords (list 
(list 1919.4375 819.237) 
(list 1845.415 819.387) 
(list 1845.415 819.21) 
(list 1919.4375 819.16)))
(apply 'command (append '("pline") coords '("c")))
(setq currobj (ssadd (entlast) currobj))
(setq coords (list 
(list 1919.4375 819.017) 
(list 1845.415 819.067) 
(list 1845.415 818.89) 
(list 1919.4375 818.94)))
(apply 'command (append '("pline") coords '("c")))
(setq currobj (ssadd (entlast) currobj))
(setq coords (list 
(list 1919.4375 818.797) 
(list 1845.415 818.747) 
(list 1845.415 818.57) 
(list 1919.4375 818.72)))
(apply 'command (append '("pline") coords '("c")))
(setq currobj (ssadd (entlast) currobj))
(setq coords (list 
(list 1919.4375 818.577) 
(list 1845.415 818.427) 
(list 1845.415 818.25) 
(list 1919.4375 818.5)))
(apply 'command (append '("pline") coords '("c")))
(setq currobj (ssadd (entlast) currobj))
(setq coords (list 
(list 1919.4375 818.357) 
(list 1845.415 818.107) 
(list 1845.415 817.93) 
(list 1919.4375 818.28)))
(apply 'command (append '("pline") coords '("c")))
(setq currobj (ssadd (entlast) currobj))
(setq coords (list 
(list 1919.4375 818.137) 
(list 1845.415 817.787) 
(list 1845.415 817.61) 
(list 1919.4375 818.06)))
(apply 'command (append '("pline") coords '("c")))
(setq currobj (ssadd (entlast) currobj))
(setq coords (list 
(list 1919.4375 817.917) 
(list 1845.415 817.467) 
(list 1845.415 817.29) 
(list 1919.4375 817.84)))
(apply 'command (append '("pline") coords '("c")))
(setq currobj (ssadd (entlast) currobj))
(setq coords (list 
(list 1919.4375 817.697) 
(list 1845.415 817.147) 
(list 1845.415 816.97) 
(list 1919.4375 817.62)))
(apply 'command (append '("pline") coords '("c")))
(setq currobj (ssadd (entlast) currobj))
(setq coords (list 
(list 1919.4375 817.477) 
(list 1845.415 816.827) 
(list 1845.415 816.65) 
(list 1919.4375 817.4)))
(apply 'command (append '("pline") coords '("c")))
(setq currobj (ssadd (entlast) currobj))
(command "_layer" "set" "nitride" "")
(command "_layer" "set" "text" "")
(command "_circle" "1919.0625,806.257" "0.075")
(command "_circle" "1919.0625,806.557" "0.075")
(command "_circle" "1919.0625,806.857" "0.075")
(command "_circle" "1919.0625,807.157" "0.075")
(command "_circle" "1919.0625,807.457" "0.075")
(command "_circle" "1918.7625,806.257" "0.075")
(command "_circle" "1918.7625,806.557" "0.075")
(command "_circle" "1918.7625,806.857" "0.075")
(command "_circle" "1918.7625,807.157" "0.075")
(command "_circle" "1918.7625,807.457" "0.075")
(command "_circle" "1918.4625,806.257" "0.075")
(command "_circle" "1918.4625,806.557" "0.075")
(command "_circle" "1918.4625,806.857" "0.075")
(command "_circle" "1918.4625,807.157" "0.075")
(command "_circle" "1918.4625,807.457" "0.075")
(command "_circle" "1918.1625,806.257" "0.075")
(command "_circle" "1918.1625,806.557" "0.075")
(command "_circle" "1918.1625,806.857" "0.075")
(command "_circle" "1918.1625,807.157" "0.075")
(command "_circle" "1918.1625,807.457" "0.075")
(command "_circle" "1917.8625,806.257" "0.075")
(command "_circle" "1917.8625,806.557" "0.075")
(command "_circle" "1917.8625,806.857" "0.075")
(command "_circle" "1917.8625,807.157" "0.075")
(command "_circle" "1917.8625,807.457" "0.075")
(command "_layer" "set" "nitride" "")
(setq coords (list 
(list 1920.2625 831.7) 
(list 1920.2625 836.7) 
(list 1919.7375 836.7) 
(list 1919.7375 831.7)))
(apply 'command (append '("pline") coords '("c")))
(setq currobj (ssadd (entlast) currobj))
(command "_layer" "set" "prebias" "")
(command "_rectangle" "1919.7375,831.7" "1920.2625,836.7")
(setq currobj (ssadd (entlast) currobj))
(command "_layer" "set" "nitride" "")
(setq cooledsinglenanobeam6 currobj)
(setq currobj nil)
(setq currobj (ssadd))
; DRAWING PHOTONIC CRYSTAL
(command "_layer" "set" "negYjunc" "")
(setq coords (list 
(list 1920.135 866.7) 
(list 1920 851.7) 
(list 1920 866.7)))
(apply 'command (append '("pline") coords '("c")))
(setq currobj (ssadd (entlast) currobj))
(setq coords (list 
(list 1920.2625 836.7) 
(list 1920.415 866.7) 
(list 1921.086 866.7) 
(list 1921.086 836.7)))
(apply 'command (append '("pline") coords '("c")))
(setq currobj (ssadd (entlast) currobj))
(setq coords (list 
(list 1919.865 866.7) 
(list 1920 851.7) 
(list 1920 866.7)))
(apply 'command (append '("pline") coords '("c")))
(setq currobj (ssadd (entlast) currobj))
(setq coords (list 
(list 1919.7375 836.7) 
(list 1919.585 866.7) 
(list 1918.914 866.7) 
(list 1918.914 836.7)))
(apply 'command (append '("pline") coords '("c")))
(setq currobj (ssadd (entlast) currobj))
(command "_layer" "set" "nitride" "")
(setq yjunction6 currobj)
(setq currobj nil)
(setq currobj (ssadd))
(setq tap6 nil)
(setq tap6 (ssadd))
(command "_layer" "set" "phc" "")
(setq coords (list 
(list 1920 866.7) 
(list 1920.135 866.7) 
(list 1920.135 866.7103) 
(list 1920.135 866.7206) 
(list 1920.135 866.7308) 
(list 1920.135 866.7411) 
(list 1920.135 866.7514) 
(list 1920.135 866.7617) 
(list 1920.135 866.7719) 
(list 1920.135 866.7822) 
(list 1920.135 866.7925) 
(list 1920.135 866.8028) 
(list 1920.135 866.8131) 
(list 1920.135 866.8233) 
(list 1920.135 866.8336) 
(list 1920.135 866.8439) 
(list 1920.135 866.8542) 
(list 1920.135 866.8644) 
(list 1920.135 866.8747) 
(list 1920.135 866.885) 
(list 1920.135 866.8953) 
(list 1920.135 866.9056) 
(list 1920.135 866.9158) 
(list 1920.135 866.9261) 
(list 1920.135 866.9364) 
(list 1920.135 866.9467) 
(list 1920.135 866.9569) 
(list 1920.135 866.9672) 
(list 1920.135 866.9775) 
(list 1920.135 866.9878) 
(list 1920.135 866.9981) 
(list 1920.135 867.0083) 
(list 1920.135 867.0186) 
(list 1920.135 867.0289) 
(list 1920.135 867.0392) 
(list 1920.135 867.0494) 
(list 1920.135 867.0597) 
(list 1920.135 867.07) 
(list 1920 867.07)))
(apply 'command (append '("pline") coords '("c")))
(setq tap6 (ssadd (entlast) tap6))
(command "_mirror" (entlast) "" "1920,900" "1920,901" "No")
(setq tap6 (ssadd (entlast) tap6))
(setq coords (list 
(list 1920.4235 866.7) 
(list 1920.415 866.7) 
(list 1920.4152 866.7103) 
(list 1920.4154 866.7206) 
(list 1920.4156 866.7308) 
(list 1920.4157 866.7411) 
(list 1920.4158 866.7514) 
(list 1920.4157 866.7617) 
(list 1920.4156 866.7719) 
(list 1920.4153 866.7822) 
(list 1920.415 866.7925) 
(list 1920.4146 866.8028) 
(list 1920.4141 866.8131) 
(list 1920.4136 866.8233) 
(list 1920.4131 866.8336) 
(list 1920.4125 866.8439) 
(list 1920.412 866.8542) 
(list 1920.4115 866.8644) 
(list 1920.4111 866.8747) 
(list 1920.4108 866.885) 
(list 1920.4106 866.8953) 
(list 1920.4106 866.9056) 
(list 1920.4108 866.9158) 
(list 1920.4111 866.9261) 
(list 1920.4116 866.9364) 
(list 1920.4122 866.9467) 
(list 1920.413 866.9569) 
(list 1920.414 866.9672) 
(list 1920.4151 866.9775) 
(list 1920.4162 866.9878) 
(list 1920.4174 866.9981) 
(list 1920.4186 867.0083) 
(list 1920.4197 867.0186) 
(list 1920.4208 867.0289) 
(list 1920.4218 867.0392) 
(list 1920.4226 867.0494) 
(list 1920.4232 867.0597) 
(list 1920.4235 867.07) 
(list 1920.4235 867.07)))
(apply 'command (append '("pline") coords '("c")))
(setq tap6 (ssadd (entlast) tap6))
(command "_mirror" (entlast) "" "1920,900" "1920,901" "No")
(setq tap6 (ssadd (entlast) tap6))
(setq coords (list 
(list 1921.086 866.7) 
(list 1920.4235 866.7) 
(list 1920.4235 866.7103) 
(list 1920.4235 866.7206) 
(list 1920.4235 866.7308) 
(list 1920.4235 866.7411) 
(list 1920.4235 866.7514) 
(list 1920.4235 866.7617) 
(list 1920.4235 866.7719) 
(list 1920.4235 866.7822) 
(list 1920.4235 866.7925) 
(list 1920.4235 866.8028) 
(list 1920.4235 866.8131) 
(list 1920.4235 866.8233) 
(list 1920.4235 866.8336) 
(list 1920.4235 866.8439) 
(list 1920.4235 866.8542) 
(list 1920.4235 866.8644) 
(list 1920.4235 866.8747) 
(list 1920.4235 866.885) 
(list 1920.4235 866.8953) 
(list 1920.4235 866.9056) 
(list 1920.4235 866.9158) 
(list 1920.4235 866.9261) 
(list 1920.4235 866.9364) 
(list 1920.4235 866.9467) 
(list 1920.4235 866.9569) 
(list 1920.4235 866.9672) 
(list 1920.4235 866.9775) 
(list 1920.4235 866.9878) 
(list 1920.4235 866.9981) 
(list 1920.4235 867.0083) 
(list 1920.4235 867.0186) 
(list 1920.4235 867.0289) 
(list 1920.4235 867.0392) 
(list 1920.4235 867.0494) 
(list 1920.4235 867.0597) 
(list 1920.4235 867.07) 
(list 1921.086 867.07)))
(apply 'command (append '("pline") coords '("c")))
(setq tap6 (ssadd (entlast) tap6))
(command "_mirror" (entlast) "" "1920,900" "1920,901" "No")
(setq tap6 (ssadd (entlast) tap6))
(setq coords (list 
(list 1920 867.07) 
(list 1920.135 867.07) 
(list 1920.135 867.0803) 
(list 1920.135 867.0906) 
(list 1920.135 867.1008) 
(list 1920.135 867.1111) 
(list 1920.135 867.1214) 
(list 1920.135 867.1317) 
(list 1920.135 867.1419) 
(list 1920.135 867.1522) 
(list 1920.135 867.1625) 
(list 1920.135 867.1728) 
(list 1920.135 867.1831) 
(list 1920.135 867.1933) 
(list 1920.135 867.2036) 
(list 1920.135 867.2139) 
(list 1920.135 867.2242) 
(list 1920.135 867.2344) 
(list 1920.135 867.2447) 
(list 1920.135 867.255) 
(list 1920.135 867.2653) 
(list 1920.135 867.2756) 
(list 1920.135 867.2858) 
(list 1920.135 867.2961) 
(list 1920.135 867.3064) 
(list 1920.135 867.3167) 
(list 1920.135 867.3269) 
(list 1920.135 867.3372) 
(list 1920.135 867.3475) 
(list 1920.135 867.3578) 
(list 1920.135 867.3681) 
(list 1920.135 867.3783) 
(list 1920.135 867.3886) 
(list 1920.135 867.3989) 
(list 1920.135 867.4092) 
(list 1920.135 867.4194) 
(list 1920.135 867.4297) 
(list 1920.135 867.44) 
(list 1920 867.44)))
(apply 'command (append '("pline") coords '("c")))
(setq tap6 (ssadd (entlast) tap6))
(command "_mirror" (entlast) "" "1920,900" "1920,901" "No")
(setq tap6 (ssadd (entlast) tap6))
(setq coords (list 
(list 1920.4321 867.07) 
(list 1920.4235 867.07) 
(list 1920.4236 867.0803) 
(list 1920.4235 867.0906) 
(list 1920.423 867.1008) 
(list 1920.4223 867.1111) 
(list 1920.4213 867.1214) 
(list 1920.42 867.1317) 
(list 1920.4185 867.1419) 
(list 1920.4169 867.1522) 
(list 1920.4151 867.1625) 
(list 1920.4132 867.1728) 
(list 1920.4113 867.1831) 
(list 1920.4094 867.1933) 
(list 1920.4077 867.2036) 
(list 1920.4061 867.2139) 
(list 1920.4047 867.2242) 
(list 1920.4036 867.2344) 
(list 1920.4028 867.2447) 
(list 1920.4024 867.255) 
(list 1920.4024 867.2653) 
(list 1920.4027 867.2756) 
(list 1920.4035 867.2858) 
(list 1920.4047 867.2961) 
(list 1920.4062 867.3064) 
(list 1920.4081 867.3167) 
(list 1920.4102 867.3269) 
(list 1920.4126 867.3372) 
(list 1920.4151 867.3475) 
(list 1920.4177 867.3578) 
(list 1920.4203 867.3681) 
(list 1920.4229 867.3783) 
(list 1920.4253 867.3886) 
(list 1920.4274 867.3989) 
(list 1920.4292 867.4092) 
(list 1920.4306 867.4194) 
(list 1920.4316 867.4297) 
(list 1920.4321 867.44) 
(list 1920.4321 867.44)))
(apply 'command (append '("pline") coords '("c")))
(setq tap6 (ssadd (entlast) tap6))
(command "_mirror" (entlast) "" "1920,900" "1920,901" "No")
(setq tap6 (ssadd (entlast) tap6))
(setq coords (list 
(list 1921.086 867.07) 
(list 1920.4321 867.07) 
(list 1920.4321 867.0803) 
(list 1920.4321 867.0906) 
(list 1920.4321 867.1008) 
(list 1920.4321 867.1111) 
(list 1920.4321 867.1214) 
(list 1920.4321 867.1317) 
(list 1920.4321 867.1419) 
(list 1920.4321 867.1522) 
(list 1920.4321 867.1625) 
(list 1920.4321 867.1728) 
(list 1920.4321 867.1831) 
(list 1920.4321 867.1933) 
(list 1920.4321 867.2036) 
(list 1920.4321 867.2139) 
(list 1920.4321 867.2242) 
(list 1920.4321 867.2344) 
(list 1920.4321 867.2447) 
(list 1920.4321 867.255) 
(list 1920.4321 867.2653) 
(list 1920.4321 867.2756) 
(list 1920.4321 867.2858) 
(list 1920.4321 867.2961) 
(list 1920.4321 867.3064) 
(list 1920.4321 867.3167) 
(list 1920.4321 867.3269) 
(list 1920.4321 867.3372) 
(list 1920.4321 867.3475) 
(list 1920.4321 867.3578) 
(list 1920.4321 867.3681) 
(list 1920.4321 867.3783) 
(list 1920.4321 867.3886) 
(list 1920.4321 867.3989) 
(list 1920.4321 867.4092) 
(list 1920.4321 867.4194) 
(list 1920.4321 867.4297) 
(list 1920.4321 867.44) 
(list 1921.086 867.44)))
(apply 'command (append '("pline") coords '("c")))
(setq tap6 (ssadd (entlast) tap6))
(command "_mirror" (entlast) "" "1920,900" "1920,901" "No")
(setq tap6 (ssadd (entlast) tap6))
(setq coords (list 
(list 1920 867.44) 
(list 1920.135 867.44) 
(list 1920.135 867.4503) 
(list 1920.135 867.4606) 
(list 1920.135 867.4708) 
(list 1920.135 867.4811) 
(list 1920.135 867.4914) 
(list 1920.135 867.5017) 
(list 1920.135 867.5119) 
(list 1920.135 867.5222) 
(list 1920.135 867.5325) 
(list 1920.135 867.5428) 
(list 1920.135 867.5531) 
(list 1920.135 867.5633) 
(list 1920.135 867.5736) 
(list 1920.135 867.5839) 
(list 1920.135 867.5942) 
(list 1920.135 867.6044) 
(list 1920.135 867.6147) 
(list 1920.135 867.625) 
(list 1920.135 867.6353) 
(list 1920.135 867.6456) 
(list 1920.135 867.6558) 
(list 1920.135 867.6661) 
(list 1920.135 867.6764) 
(list 1920.135 867.6867) 
(list 1920.135 867.6969) 
(list 1920.135 867.7072) 
(list 1920.135 867.7175) 
(list 1920.135 867.7278) 
(list 1920.135 867.7381) 
(list 1920.135 867.7483) 
(list 1920.135 867.7586) 
(list 1920.135 867.7689) 
(list 1920.135 867.7792) 
(list 1920.135 867.7894) 
(list 1920.135 867.7997) 
(list 1920.135 867.81) 
(list 1920 867.81)))
(apply 'command (append '("pline") coords '("c")))
(setq tap6 (ssadd (entlast) tap6))
(command "_mirror" (entlast) "" "1920,900" "1920,901" "No")
(setq tap6 (ssadd (entlast) tap6))
(setq coords (list 
(list 1920.4406 867.44) 
(list 1920.4321 867.44) 
(list 1920.432 867.4503) 
(list 1920.4315 867.4606) 
(list 1920.4304 867.4708) 
(list 1920.4288 867.4811) 
(list 1920.4268 867.4914) 
(list 1920.4243 867.5017) 
(list 1920.4215 867.5119) 
(list 1920.4184 867.5222) 
(list 1920.4152 867.5325) 
(list 1920.4118 867.5428) 
(list 1920.4085 867.5531) 
(list 1920.4053 867.5633) 
(list 1920.4023 867.5736) 
(list 1920.3997 867.5839) 
(list 1920.3974 867.5942) 
(list 1920.3957 867.6044) 
(list 1920.3946 867.6147) 
(list 1920.394 867.625) 
(list 1920.3941 867.6353) 
(list 1920.3948 867.6456) 
(list 1920.3962 867.6558) 
(list 1920.3982 867.6661) 
(list 1920.4008 867.6764) 
(list 1920.4039 867.6867) 
(list 1920.4074 867.6969) 
(list 1920.4112 867.7072) 
(list 1920.4152 867.7175) 
(list 1920.4193 867.7278) 
(list 1920.4233 867.7381) 
(list 1920.4272 867.7483) 
(list 1920.4308 867.7586) 
(list 1920.4339 867.7689) 
(list 1920.4366 867.7792) 
(list 1920.4386 867.7894) 
(list 1920.44 867.7997) 
(list 1920.4406 867.81) 
(list 1920.4406 867.81)))
(apply 'command (append '("pline") coords '("c")))
(setq tap6 (ssadd (entlast) tap6))
(command "_mirror" (entlast) "" "1920,900" "1920,901" "No")
(setq tap6 (ssadd (entlast) tap6))
(setq coords (list 
(list 1921.086 867.44) 
(list 1920.4406 867.44) 
(list 1920.4406 867.4503) 
(list 1920.4406 867.4606) 
(list 1920.4406 867.4708) 
(list 1920.4406 867.4811) 
(list 1920.4406 867.4914) 
(list 1920.4406 867.5017) 
(list 1920.4406 867.5119) 
(list 1920.4406 867.5222) 
(list 1920.4406 867.5325) 
(list 1920.4406 867.5428) 
(list 1920.4406 867.5531) 
(list 1920.4406 867.5633) 
(list 1920.4406 867.5736) 
(list 1920.4406 867.5839) 
(list 1920.4406 867.5942) 
(list 1920.4406 867.6044) 
(list 1920.4406 867.6147) 
(list 1920.4406 867.625) 
(list 1920.4406 867.6353) 
(list 1920.4406 867.6456) 
(list 1920.4406 867.6558) 
(list 1920.4406 867.6661) 
(list 1920.4406 867.6764) 
(list 1920.4406 867.6867) 
(list 1920.4406 867.6969) 
(list 1920.4406 867.7072) 
(list 1920.4406 867.7175) 
(list 1920.4406 867.7278) 
(list 1920.4406 867.7381) 
(list 1920.4406 867.7483) 
(list 1920.4406 867.7586) 
(list 1920.4406 867.7689) 
(list 1920.4406 867.7792) 
(list 1920.4406 867.7894) 
(list 1920.4406 867.7997) 
(list 1920.4406 867.81) 
(list 1921.086 867.81)))
(apply 'command (append '("pline") coords '("c")))
(setq tap6 (ssadd (entlast) tap6))
(command "_mirror" (entlast) "" "1920,900" "1920,901" "No")
(setq tap6 (ssadd (entlast) tap6))
(setq coords (list 
(list 1920 867.81) 
(list 1920.135 867.81) 
(list 1920.135 867.8203) 
(list 1920.135 867.8306) 
(list 1920.135 867.8408) 
(list 1920.135 867.8511) 
(list 1920.135 867.8614) 
(list 1920.135 867.8717) 
(list 1920.135 867.8819) 
(list 1920.135 867.8922) 
(list 1920.135 867.9025) 
(list 1920.135 867.9128) 
(list 1920.135 867.9231) 
(list 1920.135 867.9333) 
(list 1920.135 867.9436) 
(list 1920.135 867.9539) 
(list 1920.135 867.9642) 
(list 1920.135 867.9744) 
(list 1920.135 867.9847) 
(list 1920.135 867.995) 
(list 1920.135 868.0053) 
(list 1920.135 868.0156) 
(list 1920.135 868.0258) 
(list 1920.135 868.0361) 
(list 1920.135 868.0464) 
(list 1920.135 868.0567) 
(list 1920.135 868.0669) 
(list 1920.135 868.0772) 
(list 1920.135 868.0875) 
(list 1920.135 868.0978) 
(list 1920.135 868.1081) 
(list 1920.135 868.1183) 
(list 1920.135 868.1286) 
(list 1920.135 868.1389) 
(list 1920.135 868.1492) 
(list 1920.135 868.1594) 
(list 1920.135 868.1697) 
(list 1920.135 868.18) 
(list 1920 868.18)))
(apply 'command (append '("pline") coords '("c")))
(setq tap6 (ssadd (entlast) tap6))
(command "_mirror" (entlast) "" "1920,900" "1920,901" "No")
(setq tap6 (ssadd (entlast) tap6))
(setq coords (list 
(list 1920.4491 867.81) 
(list 1920.4406 867.81) 
(list 1920.4404 867.8203) 
(list 1920.4395 867.8306) 
(list 1920.4378 867.8408) 
(list 1920.4354 867.8511) 
(list 1920.4323 867.8614) 
(list 1920.4286 867.8717) 
(list 1920.4245 867.8819) 
(list 1920.42 867.8922) 
(list 1920.4152 867.9025) 
(list 1920.4104 867.9128) 
(list 1920.4056 867.9231) 
(list 1920.4011 867.9333) 
(list 1920.3969 867.9436) 
(list 1920.3932 867.9539) 
(list 1920.3902 867.9642) 
(list 1920.3878 867.9744) 
(list 1920.3863 867.9847) 
(list 1920.3856 867.995) 
(list 1920.3858 868.0053) 
(list 1920.3869 868.0156) 
(list 1920.389 868.0258) 
(list 1920.3918 868.0361) 
(list 1920.3954 868.0464) 
(list 1920.3997 868.0567) 
(list 1920.4045 868.0669) 
(list 1920.4098 868.0772) 
(list 1920.4153 868.0875) 
(list 1920.4208 868.0978) 
(list 1920.4263 868.1081) 
(list 1920.4315 868.1183) 
(list 1920.4363 868.1286) 
(list 1920.4405 868.1389) 
(list 1920.444 868.1492) 
(list 1920.4466 868.1594) 
(list 1920.4484 868.1697) 
(list 1920.4491 868.18) 
(list 1920.4491 868.18)))
(apply 'command (append '("pline") coords '("c")))
(setq tap6 (ssadd (entlast) tap6))
(command "_mirror" (entlast) "" "1920,900" "1920,901" "No")
(setq tap6 (ssadd (entlast) tap6))
(setq coords (list 
(list 1921.086 867.81) 
(list 1920.4491 867.81) 
(list 1920.4491 867.8203) 
(list 1920.4491 867.8306) 
(list 1920.4491 867.8408) 
(list 1920.4491 867.8511) 
(list 1920.4491 867.8614) 
(list 1920.4491 867.8717) 
(list 1920.4491 867.8819) 
(list 1920.4491 867.8922) 
(list 1920.4491 867.9025) 
(list 1920.4491 867.9128) 
(list 1920.4491 867.9231) 
(list 1920.4491 867.9333) 
(list 1920.4491 867.9436) 
(list 1920.4491 867.9539) 
(list 1920.4491 867.9642) 
(list 1920.4491 867.9744) 
(list 1920.4491 867.9847) 
(list 1920.4491 867.995) 
(list 1920.4491 868.0053) 
(list 1920.4491 868.0156) 
(list 1920.4491 868.0258) 
(list 1920.4491 868.0361) 
(list 1920.4491 868.0464) 
(list 1920.4491 868.0567) 
(list 1920.4491 868.0669) 
(list 1920.4491 868.0772) 
(list 1920.4491 868.0875) 
(list 1920.4491 868.0978) 
(list 1920.4491 868.1081) 
(list 1920.4491 868.1183) 
(list 1920.4491 868.1286) 
(list 1920.4491 868.1389) 
(list 1920.4491 868.1492) 
(list 1920.4491 868.1594) 
(list 1920.4491 868.1697) 
(list 1920.4491 868.18) 
(list 1921.086 868.18)))
(apply 'command (append '("pline") coords '("c")))
(setq tap6 (ssadd (entlast) tap6))
(command "_mirror" (entlast) "" "1920,900" "1920,901" "No")
(setq tap6 (ssadd (entlast) tap6))
(setq coords (list 
(list 1920 868.18) 
(list 1920.135 868.18) 
(list 1920.135 868.1903) 
(list 1920.135 868.2006) 
(list 1920.135 868.2108) 
(list 1920.135 868.2211) 
(list 1920.135 868.2314) 
(list 1920.135 868.2417) 
(list 1920.135 868.2519) 
(list 1920.135 868.2622) 
(list 1920.135 868.2725) 
(list 1920.135 868.2828) 
(list 1920.135 868.2931) 
(list 1920.135 868.3033) 
(list 1920.135 868.3136) 
(list 1920.135 868.3239) 
(list 1920.135 868.3342) 
(list 1920.135 868.3444) 
(list 1920.135 868.3547) 
(list 1920.135 868.365) 
(list 1920.135 868.3753) 
(list 1920.135 868.3856) 
(list 1920.135 868.3958) 
(list 1920.135 868.4061) 
(list 1920.135 868.4164) 
(list 1920.135 868.4267) 
(list 1920.135 868.4369) 
(list 1920.135 868.4472) 
(list 1920.135 868.4575) 
(list 1920.135 868.4678) 
(list 1920.135 868.4781) 
(list 1920.135 868.4883) 
(list 1920.135 868.4986) 
(list 1920.135 868.5089) 
(list 1920.135 868.5192) 
(list 1920.135 868.5294) 
(list 1920.135 868.5397) 
(list 1920.135 868.55) 
(list 1920 868.55)))
(apply 'command (append '("pline") coords '("c")))
(setq tap6 (ssadd (entlast) tap6))
(command "_mirror" (entlast) "" "1920,900" "1920,901" "No")
(setq tap6 (ssadd (entlast) tap6))
(setq coords (list 
(list 1920.4577 868.18) 
(list 1920.4491 868.18) 
(list 1920.4489 868.1903) 
(list 1920.4475 868.2006) 
(list 1920.4452 868.2108) 
(list 1920.4419 868.2211) 
(list 1920.4378 868.2314) 
(list 1920.4329 868.2417) 
(list 1920.4274 868.2519) 
(list 1920.4215 868.2622) 
(list 1920.4153 868.2725) 
(list 1920.409 868.2828) 
(list 1920.4028 868.2931) 
(list 1920.3969 868.3033) 
(list 1920.3916 868.3136) 
(list 1920.3868 868.3239) 
(list 1920.3829 868.3342) 
(list 1920.3799 868.3444) 
(list 1920.378 868.3547) 
(list 1920.3772 868.365) 
(list 1920.3775 868.3753) 
(list 1920.3791 868.3856) 
(list 1920.3817 868.3958) 
(list 1920.3854 868.4061) 
(list 1920.3901 868.4164) 
(list 1920.3956 868.4267) 
(list 1920.4017 868.4369) 
(list 1920.4084 868.4472) 
(list 1920.4153 868.4575) 
(list 1920.4223 868.4678) 
(list 1920.4292 868.4781) 
(list 1920.4358 868.4883) 
(list 1920.4418 868.4986) 
(list 1920.447 868.5089) 
(list 1920.4514 868.5192) 
(list 1920.4547 868.5294) 
(list 1920.4568 868.5397) 
(list 1920.4577 868.55) 
(list 1920.4577 868.55)))
(apply 'command (append '("pline") coords '("c")))
(setq tap6 (ssadd (entlast) tap6))
(command "_mirror" (entlast) "" "1920,900" "1920,901" "No")
(setq tap6 (ssadd (entlast) tap6))
(setq coords (list 
(list 1921.086 868.18) 
(list 1920.4577 868.18) 
(list 1920.4577 868.1903) 
(list 1920.4577 868.2006) 
(list 1920.4577 868.2108) 
(list 1920.4577 868.2211) 
(list 1920.4577 868.2314) 
(list 1920.4577 868.2417) 
(list 1920.4577 868.2519) 
(list 1920.4577 868.2622) 
(list 1920.4577 868.2725) 
(list 1920.4577 868.2828) 
(list 1920.4577 868.2931) 
(list 1920.4577 868.3033) 
(list 1920.4577 868.3136) 
(list 1920.4577 868.3239) 
(list 1920.4577 868.3342) 
(list 1920.4577 868.3444) 
(list 1920.4577 868.3547) 
(list 1920.4577 868.365) 
(list 1920.4577 868.3753) 
(list 1920.4577 868.3856) 
(list 1920.4577 868.3958) 
(list 1920.4577 868.4061) 
(list 1920.4577 868.4164) 
(list 1920.4577 868.4267) 
(list 1920.4577 868.4369) 
(list 1920.4577 868.4472) 
(list 1920.4577 868.4575) 
(list 1920.4577 868.4678) 
(list 1920.4577 868.4781) 
(list 1920.4577 868.4883) 
(list 1920.4577 868.4986) 
(list 1920.4577 868.5089) 
(list 1920.4577 868.5192) 
(list 1920.4577 868.5294) 
(list 1920.4577 868.5397) 
(list 1920.4577 868.55) 
(list 1921.086 868.55)))
(apply 'command (append '("pline") coords '("c")))
(setq tap6 (ssadd (entlast) tap6))
(command "_mirror" (entlast) "" "1920,900" "1920,901" "No")
(setq tap6 (ssadd (entlast) tap6))
(setq coords (list 
(list 1920 868.55) 
(list 1920.135 868.55) 
(list 1920.135 868.5603) 
(list 1920.135 868.5706) 
(list 1920.135 868.5808) 
(list 1920.135 868.5911) 
(list 1920.135 868.6014) 
(list 1920.135 868.6117) 
(list 1920.135 868.6219) 
(list 1920.135 868.6322) 
(list 1920.135 868.6425) 
(list 1920.135 868.6528) 
(list 1920.135 868.6631) 
(list 1920.135 868.6733) 
(list 1920.135 868.6836) 
(list 1920.135 868.6939) 
(list 1920.135 868.7042) 
(list 1920.135 868.7144) 
(list 1920.135 868.7247) 
(list 1920.135 868.735) 
(list 1920.135 868.7453) 
(list 1920.135 868.7556) 
(list 1920.135 868.7658) 
(list 1920.135 868.7761) 
(list 1920.135 868.7864) 
(list 1920.135 868.7967) 
(list 1920.135 868.8069) 
(list 1920.135 868.8172) 
(list 1920.135 868.8275) 
(list 1920.135 868.8378) 
(list 1920.135 868.8481) 
(list 1920.135 868.8583) 
(list 1920.135 868.8686) 
(list 1920.135 868.8789) 
(list 1920.135 868.8892) 
(list 1920.135 868.8994) 
(list 1920.135 868.9097) 
(list 1920.135 868.92) 
(list 1920 868.92)))
(apply 'command (append '("pline") coords '("c")))
(setq tap6 (ssadd (entlast) tap6))
(command "_mirror" (entlast) "" "1920,900" "1920,901" "No")
(setq tap6 (ssadd (entlast) tap6))
(setq coords (list 
(list 1920.4662 868.55) 
(list 1920.4577 868.55) 
(list 1920.4573 868.5603) 
(list 1920.4556 868.5706) 
(list 1920.4526 868.5808) 
(list 1920.4485 868.5911) 
(list 1920.4433 868.6014) 
(list 1920.4372 868.6117) 
(list 1920.4304 868.6219) 
(list 1920.423 868.6322) 
(list 1920.4153 868.6425) 
(list 1920.4076 868.6528) 
(list 1920.4 868.6631) 
(list 1920.3928 868.6733) 
(list 1920.3862 868.6836) 
(list 1920.3804 868.6939) 
(list 1920.3756 868.7042) 
(list 1920.372 868.7144) 
(list 1920.3697 868.7247) 
(list 1920.3688 868.735) 
(list 1920.3693 868.7453) 
(list 1920.3712 868.7556) 
(list 1920.3744 868.7658) 
(list 1920.379 868.7761) 
(list 1920.3847 868.7864) 
(list 1920.3914 868.7967) 
(list 1920.3989 868.8069) 
(list 1920.407 868.8172) 
(list 1920.4154 868.8275) 
(list 1920.4239 868.8378) 
(list 1920.4322 868.8481) 
(list 1920.4401 868.8583) 
(list 1920.4473 868.8686) 
(list 1920.4536 868.8789) 
(list 1920.4588 868.8892) 
(list 1920.4627 868.8994) 
(list 1920.4652 868.9097) 
(list 1920.4662 868.92) 
(list 1920.4662 868.92)))
(apply 'command (append '("pline") coords '("c")))
(setq tap6 (ssadd (entlast) tap6))
(command "_mirror" (entlast) "" "1920,900" "1920,901" "No")
(setq tap6 (ssadd (entlast) tap6))
(setq coords (list 
(list 1921.086 868.55) 
(list 1920.4662 868.55) 
(list 1920.4662 868.5603) 
(list 1920.4662 868.5706) 
(list 1920.4662 868.5808) 
(list 1920.4662 868.5911) 
(list 1920.4662 868.6014) 
(list 1920.4662 868.6117) 
(list 1920.4662 868.6219) 
(list 1920.4662 868.6322) 
(list 1920.4662 868.6425) 
(list 1920.4662 868.6528) 
(list 1920.4662 868.6631) 
(list 1920.4662 868.6733) 
(list 1920.4662 868.6836) 
(list 1920.4662 868.6939) 
(list 1920.4662 868.7042) 
(list 1920.4662 868.7144) 
(list 1920.4662 868.7247) 
(list 1920.4662 868.735) 
(list 1920.4662 868.7453) 
(list 1920.4662 868.7556) 
(list 1920.4662 868.7658) 
(list 1920.4662 868.7761) 
(list 1920.4662 868.7864) 
(list 1920.4662 868.7967) 
(list 1920.4662 868.8069) 
(list 1920.4662 868.8172) 
(list 1920.4662 868.8275) 
(list 1920.4662 868.8378) 
(list 1920.4662 868.8481) 
(list 1920.4662 868.8583) 
(list 1920.4662 868.8686) 
(list 1920.4662 868.8789) 
(list 1920.4662 868.8892) 
(list 1920.4662 868.8994) 
(list 1920.4662 868.9097) 
(list 1920.4662 868.92) 
(list 1921.086 868.92)))
(apply 'command (append '("pline") coords '("c")))
(setq tap6 (ssadd (entlast) tap6))
(command "_mirror" (entlast) "" "1920,900" "1920,901" "No")
(setq tap6 (ssadd (entlast) tap6))
(setq coords (list 
(list 1920 868.92) 
(list 1920.135 868.92) 
(list 1920.135 868.9303) 
(list 1920.135 868.9406) 
(list 1920.135 868.9508) 
(list 1920.135 868.9611) 
(list 1920.135 868.9714) 
(list 1920.135 868.9817) 
(list 1920.135 868.9919) 
(list 1920.135 869.0022) 
(list 1920.135 869.0125) 
(list 1920.135 869.0228) 
(list 1920.135 869.0331) 
(list 1920.135 869.0433) 
(list 1920.135 869.0536) 
(list 1920.135 869.0639) 
(list 1920.135 869.0742) 
(list 1920.135 869.0844) 
(list 1920.135 869.0947) 
(list 1920.135 869.105) 
(list 1920.135 869.1153) 
(list 1920.135 869.1256) 
(list 1920.135 869.1358) 
(list 1920.135 869.1461) 
(list 1920.135 869.1564) 
(list 1920.135 869.1667) 
(list 1920.135 869.1769) 
(list 1920.135 869.1872) 
(list 1920.135 869.1975) 
(list 1920.135 869.2078) 
(list 1920.135 869.2181) 
(list 1920.135 869.2283) 
(list 1920.135 869.2386) 
(list 1920.135 869.2489) 
(list 1920.135 869.2592) 
(list 1920.135 869.2694) 
(list 1920.135 869.2797) 
(list 1920.135 869.29) 
(list 1920 869.29)))
(apply 'command (append '("pline") coords '("c")))
(setq tap6 (ssadd (entlast) tap6))
(command "_mirror" (entlast) "" "1920,900" "1920,901" "No")
(setq tap6 (ssadd (entlast) tap6))
(setq coords (list 
(list 1920.4747 868.92) 
(list 1920.4662 868.92) 
(list 1920.4657 868.9303) 
(list 1920.4636 868.9406) 
(list 1920.46 868.9508) 
(list 1920.455 868.9611) 
(list 1920.4488 868.9714) 
(list 1920.4415 868.9817) 
(list 1920.4334 868.9919) 
(list 1920.4246 869.0022) 
(list 1920.4154 869.0125) 
(list 1920.4062 869.0228) 
(list 1920.3972 869.0331) 
(list 1920.3886 869.0433) 
(list 1920.3808 869.0536) 
(list 1920.374 869.0639) 
(list 1920.3684 869.0742) 
(list 1920.3642 869.0844) 
(list 1920.3615 869.0947) 
(list 1920.3604 869.105) 
(list 1920.361 869.1153) 
(list 1920.3633 869.1256) 
(list 1920.3672 869.1358) 
(list 1920.3726 869.1461) 
(list 1920.3793 869.1564) 
(list 1920.3872 869.1667) 
(list 1920.3961 869.1769) 
(list 1920.4056 869.1872) 
(list 1920.4154 869.1975) 
(list 1920.4254 869.2078) 
(list 1920.4352 869.2181) 
(list 1920.4444 869.2283) 
(list 1920.4528 869.2386) 
(list 1920.4601 869.2489) 
(list 1920.4662 869.2592) 
(list 1920.4707 869.2694) 
(list 1920.4736 869.2797) 
(list 1920.4747 869.29) 
(list 1920.4747 869.29)))
(apply 'command (append '("pline") coords '("c")))
(setq tap6 (ssadd (entlast) tap6))
(command "_mirror" (entlast) "" "1920,900" "1920,901" "No")
(setq tap6 (ssadd (entlast) tap6))
(setq coords (list 
(list 1921.086 868.92) 
(list 1920.4747 868.92) 
(list 1920.4747 868.9303) 
(list 1920.4747 868.9406) 
(list 1920.4747 868.9508) 
(list 1920.4747 868.9611) 
(list 1920.4747 868.9714) 
(list 1920.4747 868.9817) 
(list 1920.4747 868.9919) 
(list 1920.4747 869.0022) 
(list 1920.4747 869.0125) 
(list 1920.4747 869.0228) 
(list 1920.4747 869.0331) 
(list 1920.4747 869.0433) 
(list 1920.4747 869.0536) 
(list 1920.4747 869.0639) 
(list 1920.4747 869.0742) 
(list 1920.4747 869.0844) 
(list 1920.4747 869.0947) 
(list 1920.4747 869.105) 
(list 1920.4747 869.1153) 
(list 1920.4747 869.1256) 
(list 1920.4747 869.1358) 
(list 1920.4747 869.1461) 
(list 1920.4747 869.1564) 
(list 1920.4747 869.1667) 
(list 1920.4747 869.1769) 
(list 1920.4747 869.1872) 
(list 1920.4747 869.1975) 
(list 1920.4747 869.2078) 
(list 1920.4747 869.2181) 
(list 1920.4747 869.2283) 
(list 1920.4747 869.2386) 
(list 1920.4747 869.2489) 
(list 1920.4747 869.2592) 
(list 1920.4747 869.2694) 
(list 1920.4747 869.2797) 
(list 1920.4747 869.29) 
(list 1921.086 869.29)))
(apply 'command (append '("pline") coords '("c")))
(setq tap6 (ssadd (entlast) tap6))
(command "_mirror" (entlast) "" "1920,900" "1920,901" "No")
(setq tap6 (ssadd (entlast) tap6))
(setq coords (list 
(list 1920 869.29) 
(list 1920.135 869.29) 
(list 1920.135 869.3003) 
(list 1920.135 869.3106) 
(list 1920.135 869.3208) 
(list 1920.135 869.3311) 
(list 1920.135 869.3414) 
(list 1920.135 869.3517) 
(list 1920.135 869.3619) 
(list 1920.135 869.3722) 
(list 1920.135 869.3825) 
(list 1920.135 869.3928) 
(list 1920.135 869.4031) 
(list 1920.135 869.4133) 
(list 1920.135 869.4236) 
(list 1920.135 869.4339) 
(list 1920.135 869.4442) 
(list 1920.135 869.4544) 
(list 1920.135 869.4647) 
(list 1920.135 869.475) 
(list 1920.135 869.4853) 
(list 1920.135 869.4956) 
(list 1920.135 869.5058) 
(list 1920.135 869.5161) 
(list 1920.135 869.5264) 
(list 1920.135 869.5367) 
(list 1920.135 869.5469) 
(list 1920.135 869.5572) 
(list 1920.135 869.5675) 
(list 1920.135 869.5778) 
(list 1920.135 869.5881) 
(list 1920.135 869.5983) 
(list 1920.135 869.6086) 
(list 1920.135 869.6189) 
(list 1920.135 869.6292) 
(list 1920.135 869.6394) 
(list 1920.135 869.6497) 
(list 1920.135 869.66) 
(list 1920 869.66)))
(apply 'command (append '("pline") coords '("c")))
(setq tap6 (ssadd (entlast) tap6))
(command "_mirror" (entlast) "" "1920,900" "1920,901" "No")
(setq tap6 (ssadd (entlast) tap6))
(setq coords (list 
(list 1920.4833 869.29) 
(list 1920.4747 869.29) 
(list 1920.4741 869.3003) 
(list 1920.4716 869.3106) 
(list 1920.4674 869.3208) 
(list 1920.4616 869.3311) 
(list 1920.4543 869.3414) 
(list 1920.4458 869.3517) 
(list 1920.4363 869.3619) 
(list 1920.4261 869.3722) 
(list 1920.4155 869.3825) 
(list 1920.4048 869.3928) 
(list 1920.3943 869.4031) 
(list 1920.3844 869.4133) 
(list 1920.3754 869.4236) 
(list 1920.3676 869.4339) 
(list 1920.3611 869.4442) 
(list 1920.3563 869.4544) 
(list 1920.3532 869.4647) 
(list 1920.352 869.475) 
(list 1920.3527 869.4853) 
(list 1920.3554 869.4956) 
(list 1920.3599 869.5058) 
(list 1920.3661 869.5161) 
(list 1920.3739 869.5264) 
(list 1920.3831 869.5367) 
(list 1920.3932 869.5469) 
(list 1920.4042 869.5572) 
(list 1920.4155 869.5675) 
(list 1920.427 869.5778) 
(list 1920.4381 869.5881) 
(list 1920.4487 869.5983) 
(list 1920.4583 869.6086) 
(list 1920.4667 869.6189) 
(list 1920.4736 869.6292) 
(list 1920.4787 869.6394) 
(list 1920.482 869.6497) 
(list 1920.4833 869.66) 
(list 1920.4833 869.66)))
(apply 'command (append '("pline") coords '("c")))
(setq tap6 (ssadd (entlast) tap6))
(command "_mirror" (entlast) "" "1920,900" "1920,901" "No")
(setq tap6 (ssadd (entlast) tap6))
(setq coords (list 
(list 1921.086 869.29) 
(list 1920.4833 869.29) 
(list 1920.4833 869.3003) 
(list 1920.4833 869.3106) 
(list 1920.4833 869.3208) 
(list 1920.4833 869.3311) 
(list 1920.4833 869.3414) 
(list 1920.4833 869.3517) 
(list 1920.4833 869.3619) 
(list 1920.4833 869.3722) 
(list 1920.4833 869.3825) 
(list 1920.4833 869.3928) 
(list 1920.4833 869.4031) 
(list 1920.4833 869.4133) 
(list 1920.4833 869.4236) 
(list 1920.4833 869.4339) 
(list 1920.4833 869.4442) 
(list 1920.4833 869.4544) 
(list 1920.4833 869.4647) 
(list 1920.4833 869.475) 
(list 1920.4833 869.4853) 
(list 1920.4833 869.4956) 
(list 1920.4833 869.5058) 
(list 1920.4833 869.5161) 
(list 1920.4833 869.5264) 
(list 1920.4833 869.5367) 
(list 1920.4833 869.5469) 
(list 1920.4833 869.5572) 
(list 1920.4833 869.5675) 
(list 1920.4833 869.5778) 
(list 1920.4833 869.5881) 
(list 1920.4833 869.5983) 
(list 1920.4833 869.6086) 
(list 1920.4833 869.6189) 
(list 1920.4833 869.6292) 
(list 1920.4833 869.6394) 
(list 1920.4833 869.6497) 
(list 1920.4833 869.66) 
(list 1921.086 869.66)))
(apply 'command (append '("pline") coords '("c")))
(setq tap6 (ssadd (entlast) tap6))
(command "_mirror" (entlast) "" "1920,900" "1920,901" "No")
(setq tap6 (ssadd (entlast) tap6))
(setq coords (list 
(list 1920 869.66) 
(list 1920.135 869.66) 
(list 1920.135 869.6703) 
(list 1920.135 869.6806) 
(list 1920.135 869.6908) 
(list 1920.135 869.7011) 
(list 1920.135 869.7114) 
(list 1920.135 869.7217) 
(list 1920.135 869.7319) 
(list 1920.135 869.7422) 
(list 1920.135 869.7525) 
(list 1920.135 869.7628) 
(list 1920.135 869.7731) 
(list 1920.135 869.7833) 
(list 1920.135 869.7936) 
(list 1920.135 869.8039) 
(list 1920.135 869.8142) 
(list 1920.135 869.8244) 
(list 1920.135 869.8347) 
(list 1920.135 869.845) 
(list 1920.135 869.8553) 
(list 1920.135 869.8656) 
(list 1920.135 869.8758) 
(list 1920.135 869.8861) 
(list 1920.135 869.8964) 
(list 1920.135 869.9067) 
(list 1920.135 869.9169) 
(list 1920.135 869.9272) 
(list 1920.135 869.9375) 
(list 1920.135 869.9478) 
(list 1920.135 869.9581) 
(list 1920.135 869.9683) 
(list 1920.135 869.9786) 
(list 1920.135 869.9889) 
(list 1920.135 869.9992) 
(list 1920.135 870.0094) 
(list 1920.135 870.0197) 
(list 1920.135 870.03) 
(list 1920 870.03)))
(apply 'command (append '("pline") coords '("c")))
(setq tap6 (ssadd (entlast) tap6))
(command "_mirror" (entlast) "" "1920,900" "1920,901" "No")
(setq tap6 (ssadd (entlast) tap6))
(setq coords (list 
(list 1920.4918 869.66) 
(list 1920.4833 869.66) 
(list 1920.4825 869.6703) 
(list 1920.4796 869.6806) 
(list 1920.4748 869.6908) 
(list 1920.4681 869.7011) 
(list 1920.4598 869.7114) 
(list 1920.4501 869.7217) 
(list 1920.4393 869.7319) 
(list 1920.4276 869.7422) 
(list 1920.4155 869.7525) 
(list 1920.4034 869.7628) 
(list 1920.3915 869.7731) 
(list 1920.3803 869.7833) 
(list 1920.3701 869.7936) 
(list 1920.3611 869.8039) 
(list 1920.3538 869.8142) 
(list 1920.3484 869.8244) 
(list 1920.3449 869.8347) 
(list 1920.3436 869.845) 
(list 1920.3445 869.8553) 
(list 1920.3475 869.8656) 
(list 1920.3526 869.8758) 
(list 1920.3597 869.8861) 
(list 1920.3686 869.8964) 
(list 1920.3789 869.9067) 
(list 1920.3904 869.9169) 
(list 1920.4028 869.9272) 
(list 1920.4156 869.9375) 
(list 1920.4285 869.9478) 
(list 1920.4411 869.9581) 
(list 1920.453 869.9683) 
(list 1920.4638 869.9786) 
(list 1920.4732 869.9889) 
(list 1920.481 869.9992) 
(list 1920.4868 870.0094) 
(list 1920.4904 870.0197) 
(list 1920.4918 870.03) 
(list 1920.4918 870.03)))
(apply 'command (append '("pline") coords '("c")))
(setq tap6 (ssadd (entlast) tap6))
(command "_mirror" (entlast) "" "1920,900" "1920,901" "No")
(setq tap6 (ssadd (entlast) tap6))
(setq coords (list 
(list 1921.086 869.66) 
(list 1920.4918 869.66) 
(list 1920.4918 869.6703) 
(list 1920.4918 869.6806) 
(list 1920.4918 869.6908) 
(list 1920.4918 869.7011) 
(list 1920.4918 869.7114) 
(list 1920.4918 869.7217) 
(list 1920.4918 869.7319) 
(list 1920.4918 869.7422) 
(list 1920.4918 869.7525) 
(list 1920.4918 869.7628) 
(list 1920.4918 869.7731) 
(list 1920.4918 869.7833) 
(list 1920.4918 869.7936) 
(list 1920.4918 869.8039) 
(list 1920.4918 869.8142) 
(list 1920.4918 869.8244) 
(list 1920.4918 869.8347) 
(list 1920.4918 869.845) 
(list 1920.4918 869.8553) 
(list 1920.4918 869.8656) 
(list 1920.4918 869.8758) 
(list 1920.4918 869.8861) 
(list 1920.4918 869.8964) 
(list 1920.4918 869.9067) 
(list 1920.4918 869.9169) 
(list 1920.4918 869.9272) 
(list 1920.4918 869.9375) 
(list 1920.4918 869.9478) 
(list 1920.4918 869.9581) 
(list 1920.4918 869.9683) 
(list 1920.4918 869.9786) 
(list 1920.4918 869.9889) 
(list 1920.4918 869.9992) 
(list 1920.4918 870.0094) 
(list 1920.4918 870.0197) 
(list 1920.4918 870.03) 
(list 1921.086 870.03)))
(apply 'command (append '("pline") coords '("c")))
(setq tap6 (ssadd (entlast) tap6))
(command "_mirror" (entlast) "" "1920,900" "1920,901" "No")
(setq tap6 (ssadd (entlast) tap6))
(setq coords (list 
(list 1920 870.03) 
(list 1920.135 870.03) 
(list 1920.135 870.0403) 
(list 1920.135 870.0506) 
(list 1920.135 870.0608) 
(list 1920.135 870.0711) 
(list 1920.135 870.0814) 
(list 1920.135 870.0917) 
(list 1920.135 870.1019) 
(list 1920.135 870.1122) 
(list 1920.135 870.1225) 
(list 1920.135 870.1328) 
(list 1920.135 870.1431) 
(list 1920.135 870.1533) 
(list 1920.135 870.1636) 
(list 1920.135 870.1739) 
(list 1920.135 870.1842) 
(list 1920.135 870.1944) 
(list 1920.135 870.2047) 
(list 1920.135 870.215) 
(list 1920.135 870.2253) 
(list 1920.135 870.2356) 
(list 1920.135 870.2458) 
(list 1920.135 870.2561) 
(list 1920.135 870.2664) 
(list 1920.135 870.2767) 
(list 1920.135 870.2869) 
(list 1920.135 870.2972) 
(list 1920.135 870.3075) 
(list 1920.135 870.3178) 
(list 1920.135 870.3281) 
(list 1920.135 870.3383) 
(list 1920.135 870.3486) 
(list 1920.135 870.3589) 
(list 1920.135 870.3692) 
(list 1920.135 870.3794) 
(list 1920.135 870.3897) 
(list 1920.135 870.4) 
(list 1920 870.4)))
(apply 'command (append '("pline") coords '("c")))
(setq tap6 (ssadd (entlast) tap6))
(command "_mirror" (entlast) "" "1920,900" "1920,901" "No")
(setq tap6 (ssadd (entlast) tap6))
(setq coords (list 
(list 1920.5003 870.03) 
(list 1920.4918 870.03) 
(list 1920.4909 870.0403) 
(list 1920.4877 870.0506) 
(list 1920.4822 870.0608) 
(list 1920.4747 870.0711) 
(list 1920.4653 870.0814) 
(list 1920.4544 870.0917) 
(list 1920.4422 870.1019) 
(list 1920.4292 870.1122) 
(list 1920.4156 870.1225) 
(list 1920.402 870.1328) 
(list 1920.3887 870.1431) 
(list 1920.3761 870.1533) 
(list 1920.3647 870.1636) 
(list 1920.3547 870.1739) 
(list 1920.3466 870.1842) 
(list 1920.3405 870.1944) 
(list 1920.3367 870.2047) 
(list 1920.3352 870.215) 
(list 1920.3362 870.2253) 
(list 1920.3396 870.2356) 
(list 1920.3454 870.2458) 
(list 1920.3533 870.2561) 
(list 1920.3632 870.2664) 
(list 1920.3747 870.2767) 
(list 1920.3876 870.2869) 
(list 1920.4014 870.2972) 
(list 1920.4156 870.3075) 
(list 1920.43 870.3178) 
(list 1920.444 870.3281) 
(list 1920.4573 870.3383) 
(list 1920.4693 870.3486) 
(list 1920.4798 870.3589) 
(list 1920.4884 870.3692) 
(list 1920.4948 870.3794) 
(list 1920.4988 870.3897) 
(list 1920.5003 870.4) 
(list 1920.5003 870.4)))
(apply 'command (append '("pline") coords '("c")))
(setq tap6 (ssadd (entlast) tap6))
(command "_mirror" (entlast) "" "1920,900" "1920,901" "No")
(setq tap6 (ssadd (entlast) tap6))
(setq coords (list 
(list 1921.086 870.03) 
(list 1920.5003 870.03) 
(list 1920.5003 870.0403) 
(list 1920.5003 870.0506) 
(list 1920.5003 870.0608) 
(list 1920.5003 870.0711) 
(list 1920.5003 870.0814) 
(list 1920.5003 870.0917) 
(list 1920.5003 870.1019) 
(list 1920.5003 870.1122) 
(list 1920.5003 870.1225) 
(list 1920.5003 870.1328) 
(list 1920.5003 870.1431) 
(list 1920.5003 870.1533) 
(list 1920.5003 870.1636) 
(list 1920.5003 870.1739) 
(list 1920.5003 870.1842) 
(list 1920.5003 870.1944) 
(list 1920.5003 870.2047) 
(list 1920.5003 870.215) 
(list 1920.5003 870.2253) 
(list 1920.5003 870.2356) 
(list 1920.5003 870.2458) 
(list 1920.5003 870.2561) 
(list 1920.5003 870.2664) 
(list 1920.5003 870.2767) 
(list 1920.5003 870.2869) 
(list 1920.5003 870.2972) 
(list 1920.5003 870.3075) 
(list 1920.5003 870.3178) 
(list 1920.5003 870.3281) 
(list 1920.5003 870.3383) 
(list 1920.5003 870.3486) 
(list 1920.5003 870.3589) 
(list 1920.5003 870.3692) 
(list 1920.5003 870.3794) 
(list 1920.5003 870.3897) 
(list 1920.5003 870.4) 
(list 1921.086 870.4)))
(apply 'command (append '("pline") coords '("c")))
(setq tap6 (ssadd (entlast) tap6))
(command "_mirror" (entlast) "" "1920,900" "1920,901" "No")
(setq tap6 (ssadd (entlast) tap6))
(setq coords (list 
(list 1920 870.4) 
(list 1920.135 870.4) 
(list 1920.135 870.4103) 
(list 1920.135 870.4206) 
(list 1920.135 870.4308) 
(list 1920.135 870.4411) 
(list 1920.135 870.4514) 
(list 1920.135 870.4617) 
(list 1920.135 870.4719) 
(list 1920.135 870.4822) 
(list 1920.135 870.4925) 
(list 1920.135 870.5028) 
(list 1920.135 870.5131) 
(list 1920.135 870.5233) 
(list 1920.135 870.5336) 
(list 1920.135 870.5439) 
(list 1920.135 870.5542) 
(list 1920.135 870.5644) 
(list 1920.135 870.5747) 
(list 1920.135 870.585) 
(list 1920.135 870.5953) 
(list 1920.135 870.6056) 
(list 1920.135 870.6158) 
(list 1920.135 870.6261) 
(list 1920.135 870.6364) 
(list 1920.135 870.6467) 
(list 1920.135 870.6569) 
(list 1920.135 870.6672) 
(list 1920.135 870.6775) 
(list 1920.135 870.6878) 
(list 1920.135 870.6981) 
(list 1920.135 870.7083) 
(list 1920.135 870.7186) 
(list 1920.135 870.7289) 
(list 1920.135 870.7392) 
(list 1920.135 870.7494) 
(list 1920.135 870.7597) 
(list 1920.135 870.77) 
(list 1920 870.77)))
(apply 'command (append '("pline") coords '("c")))
(setq tap6 (ssadd (entlast) tap6))
(command "_mirror" (entlast) "" "1920,900" "1920,901" "No")
(setq tap6 (ssadd (entlast) tap6))
(setq coords (list 
(list 1920.5089 870.4) 
(list 1920.5003 870.4) 
(list 1920.4993 870.4103) 
(list 1920.4957 870.4206) 
(list 1920.4896 870.4308) 
(list 1920.4813 870.4411) 
(list 1920.4709 870.4514) 
(list 1920.4587 870.4617) 
(list 1920.4452 870.4719) 
(list 1920.4307 870.4822) 
(list 1920.4157 870.4925) 
(list 1920.4006 870.5028) 
(list 1920.3858 870.5131) 
(list 1920.3719 870.5233) 
(list 1920.3593 870.5336) 
(list 1920.3483 870.5439) 
(list 1920.3393 870.5542) 
(list 1920.3326 870.5644) 
(list 1920.3284 870.5747) 
(list 1920.3268 870.585) 
(list 1920.3279 870.5953) 
(list 1920.3317 870.6056) 
(list 1920.3381 870.6158) 
(list 1920.3469 870.6261) 
(list 1920.3578 870.6364) 
(list 1920.3706 870.6467) 
(list 1920.3847 870.6569) 
(list 1920.4 870.6672) 
(list 1920.4157 870.6775) 
(list 1920.4316 870.6878) 
(list 1920.447 870.6981) 
(list 1920.4616 870.7083) 
(list 1920.4748 870.7186) 
(list 1920.4863 870.7289) 
(list 1920.4958 870.7392) 
(list 1920.5028 870.7494) 
(list 1920.5072 870.7597) 
(list 1920.5089 870.77) 
(list 1920.5089 870.77)))
(apply 'command (append '("pline") coords '("c")))
(setq tap6 (ssadd (entlast) tap6))
(command "_mirror" (entlast) "" "1920,900" "1920,901" "No")
(setq tap6 (ssadd (entlast) tap6))
(setq coords (list 
(list 1921.086 870.4) 
(list 1920.5089 870.4) 
(list 1920.5089 870.4103) 
(list 1920.5089 870.4206) 
(list 1920.5089 870.4308) 
(list 1920.5089 870.4411) 
(list 1920.5089 870.4514) 
(list 1920.5089 870.4617) 
(list 1920.5089 870.4719) 
(list 1920.5089 870.4822) 
(list 1920.5089 870.4925) 
(list 1920.5089 870.5028) 
(list 1920.5089 870.5131) 
(list 1920.5089 870.5233) 
(list 1920.5089 870.5336) 
(list 1920.5089 870.5439) 
(list 1920.5089 870.5542) 
(list 1920.5089 870.5644) 
(list 1920.5089 870.5747) 
(list 1920.5089 870.585) 
(list 1920.5089 870.5953) 
(list 1920.5089 870.6056) 
(list 1920.5089 870.6158) 
(list 1920.5089 870.6261) 
(list 1920.5089 870.6364) 
(list 1920.5089 870.6467) 
(list 1920.5089 870.6569) 
(list 1920.5089 870.6672) 
(list 1920.5089 870.6775) 
(list 1920.5089 870.6878) 
(list 1920.5089 870.6981) 
(list 1920.5089 870.7083) 
(list 1920.5089 870.7186) 
(list 1920.5089 870.7289) 
(list 1920.5089 870.7392) 
(list 1920.5089 870.7494) 
(list 1920.5089 870.7597) 
(list 1920.5089 870.77) 
(list 1921.086 870.77)))
(apply 'command (append '("pline") coords '("c")))
(setq tap6 (ssadd (entlast) tap6))
(command "_mirror" (entlast) "" "1920,900" "1920,901" "No")
(setq tap6 (ssadd (entlast) tap6))
(setq coords (list 
(list 1920 870.77) 
(list 1920.135 870.77) 
(list 1920.135 870.7803) 
(list 1920.135 870.7906) 
(list 1920.135 870.8008) 
(list 1920.135 870.8111) 
(list 1920.135 870.8214) 
(list 1920.135 870.8317) 
(list 1920.135 870.8419) 
(list 1920.135 870.8522) 
(list 1920.135 870.8625) 
(list 1920.135 870.8728) 
(list 1920.135 870.8831) 
(list 1920.135 870.8933) 
(list 1920.135 870.9036) 
(list 1920.135 870.9139) 
(list 1920.135 870.9242) 
(list 1920.135 870.9344) 
(list 1920.135 870.9447) 
(list 1920.135 870.955) 
(list 1920.135 870.9653) 
(list 1920.135 870.9756) 
(list 1920.135 870.9858) 
(list 1920.135 870.9961) 
(list 1920.135 871.0064) 
(list 1920.135 871.0167) 
(list 1920.135 871.0269) 
(list 1920.135 871.0372) 
(list 1920.135 871.0475) 
(list 1920.135 871.0578) 
(list 1920.135 871.0681) 
(list 1920.135 871.0783) 
(list 1920.135 871.0886) 
(list 1920.135 871.0989) 
(list 1920.135 871.1092) 
(list 1920.135 871.1194) 
(list 1920.135 871.1297) 
(list 1920.135 871.14) 
(list 1920 871.14)))
(apply 'command (append '("pline") coords '("c")))
(setq tap6 (ssadd (entlast) tap6))
(command "_mirror" (entlast) "" "1920,900" "1920,901" "No")
(setq tap6 (ssadd (entlast) tap6))
(setq coords (list 
(list 1920.5174 870.77) 
(list 1920.5089 870.77) 
(list 1920.5077 870.7803) 
(list 1920.5037 870.7906) 
(list 1920.497 870.8008) 
(list 1920.4878 870.8111) 
(list 1920.4764 870.8214) 
(list 1920.463 870.8317) 
(list 1920.4482 870.8419) 
(list 1920.4322 870.8522) 
(list 1920.4157 870.8625) 
(list 1920.3992 870.8728) 
(list 1920.383 870.8831) 
(list 1920.3678 870.8933) 
(list 1920.3539 870.9036) 
(list 1920.3419 870.9139) 
(list 1920.332 870.9242) 
(list 1920.3247 870.9344) 
(list 1920.3201 870.9447) 
(list 1920.3184 870.955) 
(list 1920.3196 870.9653) 
(list 1920.3238 870.9756) 
(list 1920.3308 870.9858) 
(list 1920.3405 870.9961) 
(list 1920.3524 871.0064) 
(list 1920.3664 871.0167) 
(list 1920.3819 871.0269) 
(list 1920.3985 871.0372) 
(list 1920.4158 871.0475) 
(list 1920.4331 871.0578) 
(list 1920.45 871.0681) 
(list 1920.4659 871.0783) 
(list 1920.4803 871.0886) 
(list 1920.4929 871.0989) 
(list 1920.5032 871.1092) 
(list 1920.5108 871.1194) 
(list 1920.5156 871.1297) 
(list 1920.5174 871.14) 
(list 1920.5174 871.14)))
(apply 'command (append '("pline") coords '("c")))
(setq tap6 (ssadd (entlast) tap6))
(command "_mirror" (entlast) "" "1920,900" "1920,901" "No")
(setq tap6 (ssadd (entlast) tap6))
(setq coords (list 
(list 1921.086 870.77) 
(list 1920.5174 870.77) 
(list 1920.5174 870.7803) 
(list 1920.5174 870.7906) 
(list 1920.5174 870.8008) 
(list 1920.5174 870.8111) 
(list 1920.5174 870.8214) 
(list 1920.5174 870.8317) 
(list 1920.5174 870.8419) 
(list 1920.5174 870.8522) 
(list 1920.5174 870.8625) 
(list 1920.5174 870.8728) 
(list 1920.5174 870.8831) 
(list 1920.5174 870.8933) 
(list 1920.5174 870.9036) 
(list 1920.5174 870.9139) 
(list 1920.5174 870.9242) 
(list 1920.5174 870.9344) 
(list 1920.5174 870.9447) 
(list 1920.5174 870.955) 
(list 1920.5174 870.9653) 
(list 1920.5174 870.9756) 
(list 1920.5174 870.9858) 
(list 1920.5174 870.9961) 
(list 1920.5174 871.0064) 
(list 1920.5174 871.0167) 
(list 1920.5174 871.0269) 
(list 1920.5174 871.0372) 
(list 1920.5174 871.0475) 
(list 1920.5174 871.0578) 
(list 1920.5174 871.0681) 
(list 1920.5174 871.0783) 
(list 1920.5174 871.0886) 
(list 1920.5174 871.0989) 
(list 1920.5174 871.1092) 
(list 1920.5174 871.1194) 
(list 1920.5174 871.1297) 
(list 1920.5174 871.14) 
(list 1921.086 871.14)))
(apply 'command (append '("pline") coords '("c")))
(setq tap6 (ssadd (entlast) tap6))
(command "_mirror" (entlast) "" "1920,900" "1920,901" "No")
(setq tap6 (ssadd (entlast) tap6))
(setq coords (list 
(list 1920 871.14) 
(list 1920.135 871.14) 
(list 1920.135 871.1503) 
(list 1920.135 871.1606) 
(list 1920.135 871.1708) 
(list 1920.135 871.1811) 
(list 1920.135 871.1914) 
(list 1920.135 871.2017) 
(list 1920.135 871.2119) 
(list 1920.135 871.2222) 
(list 1920.135 871.2325) 
(list 1920.135 871.2428) 
(list 1920.135 871.2531) 
(list 1920.135 871.2633) 
(list 1920.135 871.2736) 
(list 1920.135 871.2839) 
(list 1920.135 871.2942) 
(list 1920.135 871.3044) 
(list 1920.135 871.3147) 
(list 1920.135 871.325) 
(list 1920.135 871.3353) 
(list 1920.135 871.3456) 
(list 1920.135 871.3558) 
(list 1920.135 871.3661) 
(list 1920.135 871.3764) 
(list 1920.135 871.3867) 
(list 1920.135 871.3969) 
(list 1920.135 871.4072) 
(list 1920.135 871.4175) 
(list 1920.135 871.4278) 
(list 1920.135 871.4381) 
(list 1920.135 871.4483) 
(list 1920.135 871.4586) 
(list 1920.135 871.4689) 
(list 1920.135 871.4792) 
(list 1920.135 871.4894) 
(list 1920.135 871.4997) 
(list 1920.135 871.51) 
(list 1920 871.51)))
(apply 'command (append '("pline") coords '("c")))
(setq tap6 (ssadd (entlast) tap6))
(command "_mirror" (entlast) "" "1920,900" "1920,901" "No")
(setq tap6 (ssadd (entlast) tap6))
(setq coords (list 
(list 1920.5259 871.14) 
(list 1920.5174 871.14) 
(list 1920.5161 871.1503) 
(list 1920.5117 871.1606) 
(list 1920.5044 871.1708) 
(list 1920.4944 871.1811) 
(list 1920.4819 871.1914) 
(list 1920.4673 871.2017) 
(list 1920.4511 871.2119) 
(list 1920.4338 871.2222) 
(list 1920.4158 871.2325) 
(list 1920.3978 871.2428) 
(list 1920.3802 871.2531) 
(list 1920.3636 871.2633) 
(list 1920.3486 871.2736) 
(list 1920.3355 871.2839) 
(list 1920.3248 871.2942) 
(list 1920.3168 871.3044) 
(list 1920.3118 871.3147) 
(list 1920.31 871.325) 
(list 1920.3114 871.3353) 
(list 1920.3159 871.3456) 
(list 1920.3236 871.3558) 
(list 1920.334 871.3661) 
(list 1920.3471 871.3764) 
(list 1920.3622 871.3867) 
(list 1920.3791 871.3969) 
(list 1920.3971 871.4072) 
(list 1920.4159 871.4175) 
(list 1920.4346 871.4278) 
(list 1920.4529 871.4381) 
(list 1920.4702 871.4483) 
(list 1920.4859 871.4586) 
(list 1920.4995 871.4689) 
(list 1920.5106 871.4792) 
(list 1920.5188 871.4894) 
(list 1920.524 871.4997) 
(list 1920.5259 871.51) 
(list 1920.5259 871.51)))
(apply 'command (append '("pline") coords '("c")))
(setq tap6 (ssadd (entlast) tap6))
(command "_mirror" (entlast) "" "1920,900" "1920,901" "No")
(setq tap6 (ssadd (entlast) tap6))
(setq coords (list 
(list 1921.086 871.14) 
(list 1920.5259 871.14) 
(list 1920.5259 871.1503) 
(list 1920.5259 871.1606) 
(list 1920.5259 871.1708) 
(list 1920.5259 871.1811) 
(list 1920.5259 871.1914) 
(list 1920.5259 871.2017) 
(list 1920.5259 871.2119) 
(list 1920.5259 871.2222) 
(list 1920.5259 871.2325) 
(list 1920.5259 871.2428) 
(list 1920.5259 871.2531) 
(list 1920.5259 871.2633) 
(list 1920.5259 871.2736) 
(list 1920.5259 871.2839) 
(list 1920.5259 871.2942) 
(list 1920.5259 871.3044) 
(list 1920.5259 871.3147) 
(list 1920.5259 871.325) 
(list 1920.5259 871.3353) 
(list 1920.5259 871.3456) 
(list 1920.5259 871.3558) 
(list 1920.5259 871.3661) 
(list 1920.5259 871.3764) 
(list 1920.5259 871.3867) 
(list 1920.5259 871.3969) 
(list 1920.5259 871.4072) 
(list 1920.5259 871.4175) 
(list 1920.5259 871.4278) 
(list 1920.5259 871.4381) 
(list 1920.5259 871.4483) 
(list 1920.5259 871.4586) 
(list 1920.5259 871.4689) 
(list 1920.5259 871.4792) 
(list 1920.5259 871.4894) 
(list 1920.5259 871.4997) 
(list 1920.5259 871.51) 
(list 1921.086 871.51)))
(apply 'command (append '("pline") coords '("c")))
(setq tap6 (ssadd (entlast) tap6))
(command "_mirror" (entlast) "" "1920,900" "1920,901" "No")
(setq tap6 (ssadd (entlast) tap6))
(setq coords (list 
(list 1920 871.51) 
(list 1920.135 871.51) 
(list 1920.135 871.5203) 
(list 1920.135 871.5306) 
(list 1920.135 871.5408) 
(list 1920.135 871.5511) 
(list 1920.135 871.5614) 
(list 1920.135 871.5717) 
(list 1920.135 871.5819) 
(list 1920.135 871.5922) 
(list 1920.135 871.6025) 
(list 1920.135 871.6128) 
(list 1920.135 871.6231) 
(list 1920.135 871.6333) 
(list 1920.135 871.6436) 
(list 1920.135 871.6539) 
(list 1920.135 871.6642) 
(list 1920.135 871.6744) 
(list 1920.135 871.6847) 
(list 1920.135 871.695) 
(list 1920.135 871.7053) 
(list 1920.135 871.7156) 
(list 1920.135 871.7258) 
(list 1920.135 871.7361) 
(list 1920.135 871.7464) 
(list 1920.135 871.7567) 
(list 1920.135 871.7669) 
(list 1920.135 871.7772) 
(list 1920.135 871.7875) 
(list 1920.135 871.7978) 
(list 1920.135 871.8081) 
(list 1920.135 871.8183) 
(list 1920.135 871.8286) 
(list 1920.135 871.8389) 
(list 1920.135 871.8492) 
(list 1920.135 871.8594) 
(list 1920.135 871.8697) 
(list 1920.135 871.88) 
(list 1920 871.88)))
(apply 'command (append '("pline") coords '("c")))
(setq tap6 (ssadd (entlast) tap6))
(command "_mirror" (entlast) "" "1920,900" "1920,901" "No")
(setq tap6 (ssadd (entlast) tap6))
(setq coords (list 
(list 1920.5345 871.51) 
(list 1920.5259 871.51) 
(list 1920.5245 871.5203) 
(list 1920.5197 871.5306) 
(list 1920.5118 871.5408) 
(list 1920.5009 871.5511) 
(list 1920.4874 871.5614) 
(list 1920.4716 871.5717) 
(list 1920.4541 871.5819) 
(list 1920.4353 871.5922) 
(list 1920.4159 871.6025) 
(list 1920.3964 871.6128) 
(list 1920.3774 871.6231) 
(list 1920.3594 871.6333) 
(list 1920.3432 871.6436) 
(list 1920.3291 871.6539) 
(list 1920.3175 871.6642) 
(list 1920.3089 871.6744) 
(list 1920.3036 871.6847) 
(list 1920.3016 871.695) 
(list 1920.3031 871.7053) 
(list 1920.3081 871.7156) 
(list 1920.3163 871.7258) 
(list 1920.3276 871.7361) 
(list 1920.3417 871.7464) 
(list 1920.3581 871.7567) 
(list 1920.3763 871.7669) 
(list 1920.3957 871.7772) 
(list 1920.4159 871.7875) 
(list 1920.4362 871.7978) 
(list 1920.4559 871.8081) 
(list 1920.4745 871.8183) 
(list 1920.4914 871.8286) 
(list 1920.506 871.8389) 
(list 1920.518 871.8492) 
(list 1920.5269 871.8594) 
(list 1920.5324 871.8697) 
(list 1920.5345 871.88) 
(list 1920.5345 871.88)))
(apply 'command (append '("pline") coords '("c")))
(setq tap6 (ssadd (entlast) tap6))
(command "_mirror" (entlast) "" "1920,900" "1920,901" "No")
(setq tap6 (ssadd (entlast) tap6))
(setq coords (list 
(list 1921.086 871.51) 
(list 1920.5345 871.51) 
(list 1920.5345 871.5203) 
(list 1920.5345 871.5306) 
(list 1920.5345 871.5408) 
(list 1920.5345 871.5511) 
(list 1920.5345 871.5614) 
(list 1920.5345 871.5717) 
(list 1920.5345 871.5819) 
(list 1920.5345 871.5922) 
(list 1920.5345 871.6025) 
(list 1920.5345 871.6128) 
(list 1920.5345 871.6231) 
(list 1920.5345 871.6333) 
(list 1920.5345 871.6436) 
(list 1920.5345 871.6539) 
(list 1920.5345 871.6642) 
(list 1920.5345 871.6744) 
(list 1920.5345 871.6847) 
(list 1920.5345 871.695) 
(list 1920.5345 871.7053) 
(list 1920.5345 871.7156) 
(list 1920.5345 871.7258) 
(list 1920.5345 871.7361) 
(list 1920.5345 871.7464) 
(list 1920.5345 871.7567) 
(list 1920.5345 871.7669) 
(list 1920.5345 871.7772) 
(list 1920.5345 871.7875) 
(list 1920.5345 871.7978) 
(list 1920.5345 871.8081) 
(list 1920.5345 871.8183) 
(list 1920.5345 871.8286) 
(list 1920.5345 871.8389) 
(list 1920.5345 871.8492) 
(list 1920.5345 871.8594) 
(list 1920.5345 871.8697) 
(list 1920.5345 871.88) 
(list 1921.086 871.88)))
(apply 'command (append '("pline") coords '("c")))
(setq tap6 (ssadd (entlast) tap6))
(command "_mirror" (entlast) "" "1920,900" "1920,901" "No")
(setq tap6 (ssadd (entlast) tap6))
(setq coords (list 
(list 1920 871.88) 
(list 1920.135 871.88) 
(list 1920.135 871.8903) 
(list 1920.135 871.9006) 
(list 1920.135 871.9108) 
(list 1920.135 871.9211) 
(list 1920.135 871.9314) 
(list 1920.135 871.9417) 
(list 1920.135 871.9519) 
(list 1920.135 871.9622) 
(list 1920.135 871.9725) 
(list 1920.135 871.9828) 
(list 1920.135 871.9931) 
(list 1920.135 872.0033) 
(list 1920.135 872.0136) 
(list 1920.135 872.0239) 
(list 1920.135 872.0342) 
(list 1920.135 872.0444) 
(list 1920.135 872.0547) 
(list 1920.135 872.065) 
(list 1920.135 872.0753) 
(list 1920.135 872.0856) 
(list 1920.135 872.0958) 
(list 1920.135 872.1061) 
(list 1920.135 872.1164) 
(list 1920.135 872.1267) 
(list 1920.135 872.1369) 
(list 1920.135 872.1472) 
(list 1920.135 872.1575) 
(list 1920.135 872.1678) 
(list 1920.135 872.1781) 
(list 1920.135 872.1883) 
(list 1920.135 872.1986) 
(list 1920.135 872.2089) 
(list 1920.135 872.2192) 
(list 1920.135 872.2294) 
(list 1920.135 872.2397) 
(list 1920.135 872.25) 
(list 1920 872.25)))
(apply 'command (append '("pline") coords '("c")))
(setq tap6 (ssadd (entlast) tap6))
(command "_mirror" (entlast) "" "1920,900" "1920,901" "No")
(setq tap6 (ssadd (entlast) tap6))
(setq coords (list 
(list 1920.543 871.88) 
(list 1920.5345 871.88) 
(list 1920.5329 871.8903) 
(list 1920.5278 871.9006) 
(list 1920.5192 871.9108) 
(list 1920.5075 871.9211) 
(list 1920.4929 871.9314) 
(list 1920.4759 871.9417) 
(list 1920.457 871.9519) 
(list 1920.4369 871.9622) 
(list 1920.416 871.9725) 
(list 1920.395 871.9828) 
(list 1920.3745 871.9931) 
(list 1920.3553 872.0033) 
(list 1920.3378 872.0136) 
(list 1920.3226 872.0239) 
(list 1920.3103 872.0342) 
(list 1920.301 872.0444) 
(list 1920.2953 872.0547) 
(list 1920.2932 872.065) 
(list 1920.2948 872.0753) 
(list 1920.3002 872.0856) 
(list 1920.309 872.0958) 
(list 1920.3212 872.1061) 
(list 1920.3363 872.1164) 
(list 1920.3539 872.1267) 
(list 1920.3734 872.1369) 
(list 1920.3943 872.1472) 
(list 1920.416 872.1575) 
(list 1920.4377 872.1678) 
(list 1920.4589 872.1781) 
(list 1920.4788 872.1883) 
(list 1920.4969 872.1986) 
(list 1920.5126 872.2089) 
(list 1920.5254 872.2192) 
(list 1920.5349 872.2294) 
(list 1920.5408 872.2397) 
(list 1920.543 872.25) 
(list 1920.543 872.25)))
(apply 'command (append '("pline") coords '("c")))
(setq tap6 (ssadd (entlast) tap6))
(command "_mirror" (entlast) "" "1920,900" "1920,901" "No")
(setq tap6 (ssadd (entlast) tap6))
(setq coords (list 
(list 1921.086 871.88) 
(list 1920.543 871.88) 
(list 1920.543 871.8903) 
(list 1920.543 871.9006) 
(list 1920.543 871.9108) 
(list 1920.543 871.9211) 
(list 1920.543 871.9314) 
(list 1920.543 871.9417) 
(list 1920.543 871.9519) 
(list 1920.543 871.9622) 
(list 1920.543 871.9725) 
(list 1920.543 871.9828) 
(list 1920.543 871.9931) 
(list 1920.543 872.0033) 
(list 1920.543 872.0136) 
(list 1920.543 872.0239) 
(list 1920.543 872.0342) 
(list 1920.543 872.0444) 
(list 1920.543 872.0547) 
(list 1920.543 872.065) 
(list 1920.543 872.0753) 
(list 1920.543 872.0856) 
(list 1920.543 872.0958) 
(list 1920.543 872.1061) 
(list 1920.543 872.1164) 
(list 1920.543 872.1267) 
(list 1920.543 872.1369) 
(list 1920.543 872.1472) 
(list 1920.543 872.1575) 
(list 1920.543 872.1678) 
(list 1920.543 872.1781) 
(list 1920.543 872.1883) 
(list 1920.543 872.1986) 
(list 1920.543 872.2089) 
(list 1920.543 872.2192) 
(list 1920.543 872.2294) 
(list 1920.543 872.2397) 
(list 1920.543 872.25) 
(list 1921.086 872.25)))
(apply 'command (append '("pline") coords '("c")))
(setq tap6 (ssadd (entlast) tap6))
(command "_mirror" (entlast) "" "1920,900" "1920,901" "No")
(setq tap6 (ssadd (entlast) tap6))
(command "_block" "blktap6" "1920,900" tap6 "")
(command "_insert" "blktap6" "1920,900" "1" "1" "0")
(command "_insert" "blktap6" "1920,900" "1" "1" "180")
(setq uc6 nil)
(setq uc6 (ssadd))
(setq coords (list 
(list 0 -0.185) 
(list 0.135 -0.185) 
(list 0.135 -0.17472) 
(list 0.135 -0.16444) 
(list 0.135 -0.15417) 
(list 0.135 -0.14389) 
(list 0.135 -0.13361) 
(list 0.135 -0.12333) 
(list 0.135 -0.11306) 
(list 0.135 -0.10278) 
(list 0.135 -0.0925) 
(list 0.135 -0.082222) 
(list 0.135 -0.071944) 
(list 0.135 -0.061667) 
(list 0.135 -0.051389) 
(list 0.135 -0.041111) 
(list 0.135 -0.030833) 
(list 0.135 -0.020556) 
(list 0.135 -0.010278) 
(list 0.135 0) 
(list 0.135 0.010278) 
(list 0.135 0.020556) 
(list 0.135 0.030833) 
(list 0.135 0.041111) 
(list 0.135 0.051389) 
(list 0.135 0.061667) 
(list 0.135 0.071944) 
(list 0.135 0.082222) 
(list 0.135 0.0925) 
(list 0.135 0.10278) 
(list 0.135 0.11306) 
(list 0.135 0.12333) 
(list 0.135 0.13361) 
(list 0.135 0.14389) 
(list 0.135 0.15417) 
(list 0.135 0.16444) 
(list 0.135 0.17472) 
(list 0.135 0.185) 
(list 0 0.185)))
(apply 'command (append '("pline") coords '("c")))
(setq uc6 (ssadd (entlast) uc6))
(setq coords (list 
(list 1.086 -0.185) 
(list 0.543 -0.185) 
(list 0.54107 -0.17472) 
(list 0.53534 -0.16444) 
(list 0.52599 -0.15417) 
(list 0.51329 -0.14389) 
(list 0.49763 -0.13361) 
(list 0.4795 -0.12333) 
(list 0.45944 -0.11306) 
(list 0.43805 -0.10278) 
(list 0.416 -0.0925) 
(list 0.39395 -0.082222) 
(list 0.37256 -0.071944) 
(list 0.3525 -0.061667) 
(list 0.33437 -0.051389) 
(list 0.31871 -0.041111) 
(list 0.30601 -0.030833) 
(list 0.29666 -0.020556) 
(list 0.29093 -0.010278) 
(list 0.289 0) 
(list 0.29093 0.010278) 
(list 0.29666 0.020556) 
(list 0.30601 0.030833) 
(list 0.31871 0.041111) 
(list 0.33437 0.051389) 
(list 0.3525 0.061667) 
(list 0.37256 0.071944) 
(list 0.39395 0.082222) 
(list 0.416 0.0925) 
(list 0.43805 0.10278) 
(list 0.45944 0.11306) 
(list 0.4795 0.12333) 
(list 0.49763 0.13361) 
(list 0.51329 0.14389) 
(list 0.52599 0.15417) 
(list 0.53534 0.16444) 
(list 0.54107 0.17472) 
(list 0.543 0.185) 
(list 1.086 0.185)))
(apply 'command (append '("pline") coords '("c")))
(setq uc6 (ssadd (entlast) uc6))
(command "_block" "blkuc6" "0,0.185" uc6 "")
(command "_insert" "blkuc6" "1920,872.62" "1" "1" "0")
(command "_insert" "blkuc6" "1920,872.25" "1" "1" "180")
(command "_insert" "blkuc6" "1920,872.99" "1" "1" "0")
(command "_insert" "blkuc6" "1920,872.62" "1" "1" "180")
(command "_insert" "blkuc6" "1920,873.36" "1" "1" "0")
(command "_insert" "blkuc6" "1920,872.99" "1" "1" "180")
(command "_insert" "blkuc6" "1920,873.73" "1" "1" "0")
(command "_insert" "blkuc6" "1920,873.36" "1" "1" "180")
(command "_insert" "blkuc6" "1920,874.1" "1" "1" "0")
(command "_insert" "blkuc6" "1920,873.73" "1" "1" "180")
(command "_insert" "blkuc6" "1920,874.47" "1" "1" "0")
(command "_insert" "blkuc6" "1920,874.1" "1" "1" "180")
(command "_insert" "blkuc6" "1920,874.84" "1" "1" "0")
(command "_insert" "blkuc6" "1920,874.47" "1" "1" "180")
(command "_insert" "blkuc6" "1920,875.21" "1" "1" "0")
(command "_insert" "blkuc6" "1920,874.84" "1" "1" "180")
(command "_insert" "blkuc6" "1920,875.58" "1" "1" "0")
(command "_insert" "blkuc6" "1920,875.21" "1" "1" "180")
(command "_insert" "blkuc6" "1920,875.95" "1" "1" "0")
(command "_insert" "blkuc6" "1920,875.58" "1" "1" "180")
(command "_insert" "blkuc6" "1920,876.32" "1" "1" "0")
(command "_insert" "blkuc6" "1920,875.95" "1" "1" "180")
(command "_insert" "blkuc6" "1920,876.69" "1" "1" "0")
(command "_insert" "blkuc6" "1920,876.32" "1" "1" "180")
(command "_insert" "blkuc6" "1920,877.06" "1" "1" "0")
(command "_insert" "blkuc6" "1920,876.69" "1" "1" "180")
(command "_insert" "blkuc6" "1920,877.43" "1" "1" "0")
(command "_insert" "blkuc6" "1920,877.06" "1" "1" "180")
(command "_insert" "blkuc6" "1920,877.8" "1" "1" "0")
(command "_insert" "blkuc6" "1920,877.43" "1" "1" "180")
(command "_insert" "blkuc6" "1920,878.17" "1" "1" "0")
(command "_insert" "blkuc6" "1920,877.8" "1" "1" "180")
(command "_insert" "blkuc6" "1920,878.54" "1" "1" "0")
(command "_insert" "blkuc6" "1920,878.17" "1" "1" "180")
(command "_insert" "blkuc6" "1920,878.91" "1" "1" "0")
(command "_insert" "blkuc6" "1920,878.54" "1" "1" "180")
(command "_insert" "blkuc6" "1920,879.28" "1" "1" "0")
(command "_insert" "blkuc6" "1920,878.91" "1" "1" "180")
(command "_insert" "blkuc6" "1920,879.65" "1" "1" "0")
(command "_insert" "blkuc6" "1920,879.28" "1" "1" "180")
(command "_insert" "blkuc6" "1920,880.02" "1" "1" "0")
(command "_insert" "blkuc6" "1920,879.65" "1" "1" "180")
(command "_insert" "blkuc6" "1920,880.39" "1" "1" "0")
(command "_insert" "blkuc6" "1920,880.02" "1" "1" "180")
(command "_insert" "blkuc6" "1920,880.76" "1" "1" "0")
(command "_insert" "blkuc6" "1920,880.39" "1" "1" "180")
(command "_insert" "blkuc6" "1920,881.13" "1" "1" "0")
(command "_insert" "blkuc6" "1920,880.76" "1" "1" "180")
(command "_insert" "blkuc6" "1920,881.5" "1" "1" "0")
(command "_insert" "blkuc6" "1920,881.13" "1" "1" "180")
(command "_insert" "blkuc6" "1920,881.87" "1" "1" "0")
(command "_insert" "blkuc6" "1920,881.5" "1" "1" "180")
(command "_insert" "blkuc6" "1920,882.24" "1" "1" "0")
(command "_insert" "blkuc6" "1920,881.87" "1" "1" "180")
(command "_insert" "blkuc6" "1920,882.61" "1" "1" "0")
(command "_insert" "blkuc6" "1920,882.24" "1" "1" "180")
(command "_insert" "blkuc6" "1920,882.98" "1" "1" "0")
(command "_insert" "blkuc6" "1920,882.61" "1" "1" "180")
(command "_insert" "blkuc6" "1920,883.35" "1" "1" "0")
(command "_insert" "blkuc6" "1920,882.98" "1" "1" "180")
(command "_insert" "blkuc6" "1920,883.72" "1" "1" "0")
(command "_insert" "blkuc6" "1920,883.35" "1" "1" "180")
(command "_insert" "blkuc6" "1920,884.09" "1" "1" "0")
(command "_insert" "blkuc6" "1920,883.72" "1" "1" "180")
(command "_insert" "blkuc6" "1920,884.46" "1" "1" "0")
(command "_insert" "blkuc6" "1920,884.09" "1" "1" "180")
(command "_insert" "blkuc6" "1920,884.83" "1" "1" "0")
(command "_insert" "blkuc6" "1920,884.46" "1" "1" "180")
(command "_insert" "blkuc6" "1920,885.2" "1" "1" "0")
(command "_insert" "blkuc6" "1920,884.83" "1" "1" "180")
(command "_insert" "blkuc6" "1920,885.57" "1" "1" "0")
(command "_insert" "blkuc6" "1920,885.2" "1" "1" "180")
(command "_insert" "blkuc6" "1920,885.94" "1" "1" "0")
(command "_insert" "blkuc6" "1920,885.57" "1" "1" "180")
(command "_insert" "blkuc6" "1920,886.31" "1" "1" "0")
(command "_insert" "blkuc6" "1920,885.94" "1" "1" "180")
(command "_insert" "blkuc6" "1920,886.68" "1" "1" "0")
(command "_insert" "blkuc6" "1920,886.31" "1" "1" "180")
(command "_insert" "blkuc6" "1920,887.05" "1" "1" "0")
(command "_insert" "blkuc6" "1920,886.68" "1" "1" "180")
(command "_insert" "blkuc6" "1920,887.42" "1" "1" "0")
(command "_insert" "blkuc6" "1920,887.05" "1" "1" "180")
(command "_insert" "blkuc6" "1920,887.79" "1" "1" "0")
(command "_insert" "blkuc6" "1920,887.42" "1" "1" "180")
(command "_insert" "blkuc6" "1920,888.16" "1" "1" "0")
(command "_insert" "blkuc6" "1920,887.79" "1" "1" "180")
(command "_insert" "blkuc6" "1920,888.53" "1" "1" "0")
(command "_insert" "blkuc6" "1920,888.16" "1" "1" "180")
(command "_insert" "blkuc6" "1920,888.9" "1" "1" "0")
(command "_insert" "blkuc6" "1920,888.53" "1" "1" "180")
(command "_insert" "blkuc6" "1920,889.27" "1" "1" "0")
(command "_insert" "blkuc6" "1920,888.9" "1" "1" "180")
(command "_insert" "blkuc6" "1920,889.64" "1" "1" "0")
(command "_insert" "blkuc6" "1920,889.27" "1" "1" "180")
(command "_insert" "blkuc6" "1920,890.01" "1" "1" "0")
(command "_insert" "blkuc6" "1920,889.64" "1" "1" "180")
(command "_insert" "blkuc6" "1920,890.38" "1" "1" "0")
(command "_insert" "blkuc6" "1920,890.01" "1" "1" "180")
(command "_insert" "blkuc6" "1920,890.75" "1" "1" "0")
(command "_insert" "blkuc6" "1920,890.38" "1" "1" "180")
(command "_insert" "blkuc6" "1920,891.12" "1" "1" "0")
(command "_insert" "blkuc6" "1920,890.75" "1" "1" "180")
(command "_insert" "blkuc6" "1920,891.49" "1" "1" "0")
(command "_insert" "blkuc6" "1920,891.12" "1" "1" "180")
(command "_insert" "blkuc6" "1920,891.86" "1" "1" "0")
(command "_insert" "blkuc6" "1920,891.49" "1" "1" "180")
(command "_insert" "blkuc6" "1920,892.23" "1" "1" "0")
(command "_insert" "blkuc6" "1920,891.86" "1" "1" "180")
(command "_insert" "blkuc6" "1920,892.6" "1" "1" "0")
(command "_insert" "blkuc6" "1920,892.23" "1" "1" "180")
(command "_insert" "blkuc6" "1920,892.97" "1" "1" "0")
(command "_insert" "blkuc6" "1920,892.6" "1" "1" "180")
(command "_insert" "blkuc6" "1920,893.34" "1" "1" "0")
(command "_insert" "blkuc6" "1920,892.97" "1" "1" "180")
(command "_insert" "blkuc6" "1920,893.71" "1" "1" "0")
(command "_insert" "blkuc6" "1920,893.34" "1" "1" "180")
(command "_insert" "blkuc6" "1920,894.08" "1" "1" "0")
(command "_insert" "blkuc6" "1920,893.71" "1" "1" "180")
(command "_insert" "blkuc6" "1920,894.45" "1" "1" "0")
(command "_insert" "blkuc6" "1920,894.08" "1" "1" "180")
(command "_insert" "blkuc6" "1920,894.82" "1" "1" "0")
(command "_insert" "blkuc6" "1920,894.45" "1" "1" "180")
(command "_insert" "blkuc6" "1920,895.19" "1" "1" "0")
(command "_insert" "blkuc6" "1920,894.82" "1" "1" "180")
(command "_insert" "blkuc6" "1920,895.56" "1" "1" "0")
(command "_insert" "blkuc6" "1920,895.19" "1" "1" "180")
(command "_insert" "blkuc6" "1920,895.93" "1" "1" "0")
(command "_insert" "blkuc6" "1920,895.56" "1" "1" "180")
(command "_insert" "blkuc6" "1920,896.3" "1" "1" "0")
(command "_insert" "blkuc6" "1920,895.93" "1" "1" "180")
(command "_insert" "blkuc6" "1920,896.67" "1" "1" "0")
(command "_insert" "blkuc6" "1920,896.3" "1" "1" "180")
(command "_insert" "blkuc6" "1920,897.04" "1" "1" "0")
(command "_insert" "blkuc6" "1920,896.67" "1" "1" "180")
(command "_insert" "blkuc6" "1920,897.41" "1" "1" "0")
(command "_insert" "blkuc6" "1920,897.04" "1" "1" "180")
(command "_insert" "blkuc6" "1920,897.78" "1" "1" "0")
(command "_insert" "blkuc6" "1920,897.41" "1" "1" "180")
(command "_insert" "blkuc6" "1920,898.15" "1" "1" "0")
(command "_insert" "blkuc6" "1920,897.78" "1" "1" "180")
(command "_insert" "blkuc6" "1920,898.52" "1" "1" "0")
(command "_insert" "blkuc6" "1920,898.15" "1" "1" "180")
(command "_insert" "blkuc6" "1920,898.89" "1" "1" "0")
(command "_insert" "blkuc6" "1920,898.52" "1" "1" "180")
(command "_insert" "blkuc6" "1920,899.26" "1" "1" "0")
(command "_insert" "blkuc6" "1920,898.89" "1" "1" "180")
(command "_insert" "blkuc6" "1920,899.63" "1" "1" "0")
(command "_insert" "blkuc6" "1920,899.26" "1" "1" "180")
(command "_insert" "blkuc6" "1920,900" "1" "1" "0")
(command "_insert" "blkuc6" "1920,899.63" "1" "1" "180")
(command "_insert" "blkuc6" "1920,900.37" "1" "1" "0")
(command "_insert" "blkuc6" "1920,900" "1" "1" "180")
(command "_insert" "blkuc6" "1920,900.74" "1" "1" "0")
(command "_insert" "blkuc6" "1920,900.37" "1" "1" "180")
(command "_insert" "blkuc6" "1920,901.11" "1" "1" "0")
(command "_insert" "blkuc6" "1920,900.74" "1" "1" "180")
(command "_insert" "blkuc6" "1920,901.48" "1" "1" "0")
(command "_insert" "blkuc6" "1920,901.11" "1" "1" "180")
(command "_insert" "blkuc6" "1920,901.85" "1" "1" "0")
(command "_insert" "blkuc6" "1920,901.48" "1" "1" "180")
(command "_insert" "blkuc6" "1920,902.22" "1" "1" "0")
(command "_insert" "blkuc6" "1920,901.85" "1" "1" "180")
(command "_insert" "blkuc6" "1920,902.59" "1" "1" "0")
(command "_insert" "blkuc6" "1920,902.22" "1" "1" "180")
(command "_insert" "blkuc6" "1920,902.96" "1" "1" "0")
(command "_insert" "blkuc6" "1920,902.59" "1" "1" "180")
(command "_insert" "blkuc6" "1920,903.33" "1" "1" "0")
(command "_insert" "blkuc6" "1920,902.96" "1" "1" "180")
(command "_insert" "blkuc6" "1920,903.7" "1" "1" "0")
(command "_insert" "blkuc6" "1920,903.33" "1" "1" "180")
(command "_insert" "blkuc6" "1920,904.07" "1" "1" "0")
(command "_insert" "blkuc6" "1920,903.7" "1" "1" "180")
(command "_insert" "blkuc6" "1920,904.44" "1" "1" "0")
(command "_insert" "blkuc6" "1920,904.07" "1" "1" "180")
(command "_insert" "blkuc6" "1920,904.81" "1" "1" "0")
(command "_insert" "blkuc6" "1920,904.44" "1" "1" "180")
(command "_insert" "blkuc6" "1920,905.18" "1" "1" "0")
(command "_insert" "blkuc6" "1920,904.81" "1" "1" "180")
(command "_insert" "blkuc6" "1920,905.55" "1" "1" "0")
(command "_insert" "blkuc6" "1920,905.18" "1" "1" "180")
(command "_insert" "blkuc6" "1920,905.92" "1" "1" "0")
(command "_insert" "blkuc6" "1920,905.55" "1" "1" "180")
(command "_insert" "blkuc6" "1920,906.29" "1" "1" "0")
(command "_insert" "blkuc6" "1920,905.92" "1" "1" "180")
(command "_insert" "blkuc6" "1920,906.66" "1" "1" "0")
(command "_insert" "blkuc6" "1920,906.29" "1" "1" "180")
(command "_insert" "blkuc6" "1920,907.03" "1" "1" "0")
(command "_insert" "blkuc6" "1920,906.66" "1" "1" "180")
(command "_insert" "blkuc6" "1920,907.4" "1" "1" "0")
(command "_insert" "blkuc6" "1920,907.03" "1" "1" "180")
(command "_insert" "blkuc6" "1920,907.77" "1" "1" "0")
(command "_insert" "blkuc6" "1920,907.4" "1" "1" "180")
(command "_insert" "blkuc6" "1920,908.14" "1" "1" "0")
(command "_insert" "blkuc6" "1920,907.77" "1" "1" "180")
(command "_insert" "blkuc6" "1920,908.51" "1" "1" "0")
(command "_insert" "blkuc6" "1920,908.14" "1" "1" "180")
(command "_insert" "blkuc6" "1920,908.88" "1" "1" "0")
(command "_insert" "blkuc6" "1920,908.51" "1" "1" "180")
(command "_insert" "blkuc6" "1920,909.25" "1" "1" "0")
(command "_insert" "blkuc6" "1920,908.88" "1" "1" "180")
(command "_insert" "blkuc6" "1920,909.62" "1" "1" "0")
(command "_insert" "blkuc6" "1920,909.25" "1" "1" "180")
(command "_insert" "blkuc6" "1920,909.99" "1" "1" "0")
(command "_insert" "blkuc6" "1920,909.62" "1" "1" "180")
(command "_insert" "blkuc6" "1920,910.36" "1" "1" "0")
(command "_insert" "blkuc6" "1920,909.99" "1" "1" "180")
(command "_insert" "blkuc6" "1920,910.73" "1" "1" "0")
(command "_insert" "blkuc6" "1920,910.36" "1" "1" "180")
(command "_insert" "blkuc6" "1920,911.1" "1" "1" "0")
(command "_insert" "blkuc6" "1920,910.73" "1" "1" "180")
(command "_insert" "blkuc6" "1920,911.47" "1" "1" "0")
(command "_insert" "blkuc6" "1920,911.1" "1" "1" "180")
(command "_insert" "blkuc6" "1920,911.84" "1" "1" "0")
(command "_insert" "blkuc6" "1920,911.47" "1" "1" "180")
(command "_insert" "blkuc6" "1920,912.21" "1" "1" "0")
(command "_insert" "blkuc6" "1920,911.84" "1" "1" "180")
(command "_insert" "blkuc6" "1920,912.58" "1" "1" "0")
(command "_insert" "blkuc6" "1920,912.21" "1" "1" "180")
(command "_insert" "blkuc6" "1920,912.95" "1" "1" "0")
(command "_insert" "blkuc6" "1920,912.58" "1" "1" "180")
(command "_insert" "blkuc6" "1920,913.32" "1" "1" "0")
(command "_insert" "blkuc6" "1920,912.95" "1" "1" "180")
(command "_insert" "blkuc6" "1920,913.69" "1" "1" "0")
(command "_insert" "blkuc6" "1920,913.32" "1" "1" "180")
(command "_insert" "blkuc6" "1920,914.06" "1" "1" "0")
(command "_insert" "blkuc6" "1920,913.69" "1" "1" "180")
(command "_insert" "blkuc6" "1920,914.43" "1" "1" "0")
(command "_insert" "blkuc6" "1920,914.06" "1" "1" "180")
(command "_insert" "blkuc6" "1920,914.8" "1" "1" "0")
(command "_insert" "blkuc6" "1920,914.43" "1" "1" "180")
(command "_insert" "blkuc6" "1920,915.17" "1" "1" "0")
(command "_insert" "blkuc6" "1920,914.8" "1" "1" "180")
(command "_insert" "blkuc6" "1920,915.54" "1" "1" "0")
(command "_insert" "blkuc6" "1920,915.17" "1" "1" "180")
(command "_insert" "blkuc6" "1920,915.91" "1" "1" "0")
(command "_insert" "blkuc6" "1920,915.54" "1" "1" "180")
(command "_insert" "blkuc6" "1920,916.28" "1" "1" "0")
(command "_insert" "blkuc6" "1920,915.91" "1" "1" "180")
(command "_insert" "blkuc6" "1920,916.65" "1" "1" "0")
(command "_insert" "blkuc6" "1920,916.28" "1" "1" "180")
(command "_insert" "blkuc6" "1920,917.02" "1" "1" "0")
(command "_insert" "blkuc6" "1920,916.65" "1" "1" "180")
(command "_insert" "blkuc6" "1920,917.39" "1" "1" "0")
(command "_insert" "blkuc6" "1920,917.02" "1" "1" "180")
(command "_insert" "blkuc6" "1920,917.76" "1" "1" "0")
(command "_insert" "blkuc6" "1920,917.39" "1" "1" "180")
(command "_insert" "blkuc6" "1920,918.13" "1" "1" "0")
(command "_insert" "blkuc6" "1920,917.76" "1" "1" "180")
(command "_insert" "blkuc6" "1920,918.5" "1" "1" "0")
(command "_insert" "blkuc6" "1920,918.13" "1" "1" "180")
(command "_insert" "blkuc6" "1920,918.87" "1" "1" "0")
(command "_insert" "blkuc6" "1920,918.5" "1" "1" "180")
(command "_insert" "blkuc6" "1920,919.24" "1" "1" "0")
(command "_insert" "blkuc6" "1920,918.87" "1" "1" "180")
(command "_insert" "blkuc6" "1920,919.61" "1" "1" "0")
(command "_insert" "blkuc6" "1920,919.24" "1" "1" "180")
(command "_insert" "blkuc6" "1920,919.98" "1" "1" "0")
(command "_insert" "blkuc6" "1920,919.61" "1" "1" "180")
(command "_insert" "blkuc6" "1920,920.35" "1" "1" "0")
(command "_insert" "blkuc6" "1920,919.98" "1" "1" "180")
(command "_insert" "blkuc6" "1920,920.72" "1" "1" "0")
(command "_insert" "blkuc6" "1920,920.35" "1" "1" "180")
(command "_insert" "blkuc6" "1920,921.09" "1" "1" "0")
(command "_insert" "blkuc6" "1920,920.72" "1" "1" "180")
(command "_insert" "blkuc6" "1920,921.46" "1" "1" "0")
(command "_insert" "blkuc6" "1920,921.09" "1" "1" "180")
(command "_insert" "blkuc6" "1920,921.83" "1" "1" "0")
(command "_insert" "blkuc6" "1920,921.46" "1" "1" "180")
(command "_insert" "blkuc6" "1920,922.2" "1" "1" "0")
(command "_insert" "blkuc6" "1920,921.83" "1" "1" "180")
(command "_insert" "blkuc6" "1920,922.57" "1" "1" "0")
(command "_insert" "blkuc6" "1920,922.2" "1" "1" "180")
(command "_insert" "blkuc6" "1920,922.94" "1" "1" "0")
(command "_insert" "blkuc6" "1920,922.57" "1" "1" "180")
(command "_insert" "blkuc6" "1920,923.31" "1" "1" "0")
(command "_insert" "blkuc6" "1920,922.94" "1" "1" "180")
(command "_insert" "blkuc6" "1920,923.68" "1" "1" "0")
(command "_insert" "blkuc6" "1920,923.31" "1" "1" "180")
(command "_insert" "blkuc6" "1920,924.05" "1" "1" "0")
(command "_insert" "blkuc6" "1920,923.68" "1" "1" "180")
(command "_insert" "blkuc6" "1920,924.42" "1" "1" "0")
(command "_insert" "blkuc6" "1920,924.05" "1" "1" "180")
(command "_insert" "blkuc6" "1920,924.79" "1" "1" "0")
(command "_insert" "blkuc6" "1920,924.42" "1" "1" "180")
(command "_insert" "blkuc6" "1920,925.16" "1" "1" "0")
(command "_insert" "blkuc6" "1920,924.79" "1" "1" "180")
(command "_insert" "blkuc6" "1920,925.53" "1" "1" "0")
(command "_insert" "blkuc6" "1920,925.16" "1" "1" "180")
(command "_insert" "blkuc6" "1920,925.9" "1" "1" "0")
(command "_insert" "blkuc6" "1920,925.53" "1" "1" "180")
(command "_insert" "blkuc6" "1920,926.27" "1" "1" "0")
(command "_insert" "blkuc6" "1920,925.9" "1" "1" "180")
(command "_insert" "blkuc6" "1920,926.64" "1" "1" "0")
(command "_insert" "blkuc6" "1920,926.27" "1" "1" "180")
(command "_insert" "blkuc6" "1920,927.01" "1" "1" "0")
(command "_insert" "blkuc6" "1920,926.64" "1" "1" "180")
(command "_insert" "blkuc6" "1920,927.38" "1" "1" "0")
(command "_insert" "blkuc6" "1920,927.01" "1" "1" "180")
(command "_insert" "blkuc6" "1920,927.75" "1" "1" "0")
(command "_insert" "blkuc6" "1920,927.38" "1" "1" "180")
(command "_layer" "set" "phccover" "")
(command "_rectangle" "1918.914,933.3" "1921.086,866.7")
(command "_layer" "set" "nitride" "")
(setq phc6 currobj)
(command "_layer" "set" "cover" "")
(command "_rectangle" "1918.914,836.7" "1921.086,963.3")
(command "_layer" "set" "nitride" "")
(command "_layer" "set" "text" "")
(command "_circle" "1917.964,846.7" "0.075")
(command "_circle" "1917.589,846.7" "0.15")
(command "_circle" "1917.214,846.7" "0.075")
(command "_circle" "1916.839,846.7" "0.15")
(command "_circle" "1917.964,848.7" "0.075")
(command "_circle" "1917.589,848.7" "0.075")
(command "_circle" "1917.214,848.7" "0.15")
(command "_circle" "1916.839,848.7" "0.15")
(command "_circle" "1917.964,850.7" "0.075")
(command "_circle" "1917.589,850.7" "0.15")
(command "_circle" "1917.214,850.7" "0.15")
(command "_circle" "1916.839,850.7" "0.15")
(command "_circle" "1917.964,852.7" "0.075")
(command "_circle" "1917.589,852.7" "0.075")
(command "_circle" "1917.214,852.7" "0.075")
(command "_circle" "1916.839,852.7" "0.075")
(command "_circle" "1916.464,852.7" "0.15")
(command "_circle" "1917.964,854.7" "0.075")
(command "_circle" "1917.589,854.7" "0.15")
(command "_circle" "1917.214,854.7" "0.075")
(command "_circle" "1916.839,854.7" "0.075")
(command "_circle" "1916.464,854.7" "0.15")
(command "_circle" "1917.964,856.7" "0.075")
(command "_circle" "1917.589,856.7" "0.075")
(command "_circle" "1917.214,856.7" "0.15")
(command "_circle" "1916.839,856.7" "0.075")
(command "_circle" "1916.464,856.7" "0.15")
(command "_circle" "1917.964,858.7" "0.075")
(command "_circle" "1917.589,858.7" "0.15")
(command "_circle" "1917.214,858.7" "0.15")
(command "_circle" "1916.839,858.7" "0.075")
(command "_circle" "1916.464,858.7" "0.15")
(command "_circle" "1917.964,860.7" "0.075")
(command "_circle" "1917.589,860.7" "0.075")
(command "_circle" "1917.214,860.7" "0.075")
(command "_circle" "1916.839,860.7" "0.15")
(command "_circle" "1916.464,860.7" "0.15")
(command "_circle" "1917.964,862.7" "0.075")
(command "_circle" "1917.589,862.7" "0.15")
(command "_circle" "1917.214,862.7" "0.075")
(command "_circle" "1916.839,862.7" "0.15")
(command "_circle" "1916.464,862.7" "0.15")
(command "_circle" "1917.964,864.7" "0.075")
(command "_circle" "1917.589,864.7" "0.075")
(command "_circle" "1917.214,864.7" "0.15")
(command "_circle" "1916.839,864.7" "0.15")
(command "_circle" "1916.464,864.7" "0.15")
(command "_circle" "1917.964,866.7" "0.075")
(command "_circle" "1917.589,866.7" "0.15")
(command "_circle" "1917.214,866.7" "0.15")
(command "_circle" "1916.839,866.7" "0.15")
(command "_circle" "1916.464,866.7" "0.15")
(command "_circle" "1917.964,868.7" "0.075")
(command "_circle" "1917.589,868.7" "0.075")
(command "_circle" "1917.214,868.7" "0.075")
(command "_circle" "1916.839,868.7" "0.075")
(command "_circle" "1916.464,868.7" "0.075")
(command "_circle" "1916.089,868.7" "0.15")
(command "_circle" "1917.964,870.7" "0.075")
(command "_circle" "1917.589,870.7" "0.15")
(command "_circle" "1917.214,870.7" "0.075")
(command "_circle" "1916.839,870.7" "0.075")
(command "_circle" "1916.464,870.7" "0.075")
(command "_circle" "1916.089,870.7" "0.15")
(command "_circle" "1917.964,872.7" "0.075")
(command "_circle" "1917.589,872.7" "0.075")
(command "_circle" "1917.214,872.7" "0.15")
(command "_circle" "1916.839,872.7" "0.075")
(command "_circle" "1916.464,872.7" "0.075")
(command "_circle" "1916.089,872.7" "0.15")
(command "_circle" "1917.964,874.7" "0.075")
(command "_circle" "1917.589,874.7" "0.15")
(command "_circle" "1917.214,874.7" "0.15")
(command "_circle" "1916.839,874.7" "0.075")
(command "_circle" "1916.464,874.7" "0.075")
(command "_circle" "1916.089,874.7" "0.15")
(command "_circle" "1917.964,876.7" "0.075")
(command "_circle" "1917.589,876.7" "0.075")
(command "_circle" "1917.214,876.7" "0.075")
(command "_circle" "1916.839,876.7" "0.15")
(command "_circle" "1916.464,876.7" "0.075")
(command "_circle" "1916.089,876.7" "0.15")
(command "_circle" "1917.964,878.7" "0.075")
(command "_circle" "1917.589,878.7" "0.15")
(command "_circle" "1917.214,878.7" "0.075")
(command "_circle" "1916.839,878.7" "0.15")
(command "_circle" "1916.464,878.7" "0.075")
(command "_circle" "1916.089,878.7" "0.15")
(command "_circle" "1917.964,880.7" "0.075")
(command "_circle" "1917.589,880.7" "0.075")
(command "_circle" "1917.214,880.7" "0.15")
(command "_circle" "1916.839,880.7" "0.15")
(command "_circle" "1916.464,880.7" "0.075")
(command "_circle" "1916.089,880.7" "0.15")
(command "_circle" "1917.964,882.7" "0.075")
(command "_circle" "1917.589,882.7" "0.15")
(command "_circle" "1917.214,882.7" "0.15")
(command "_circle" "1916.839,882.7" "0.15")
(command "_circle" "1916.464,882.7" "0.075")
(command "_circle" "1916.089,882.7" "0.15")
(command "_circle" "1917.964,884.7" "0.075")
(command "_circle" "1917.589,884.7" "0.075")
(command "_circle" "1917.214,884.7" "0.075")
(command "_circle" "1916.839,884.7" "0.075")
(command "_circle" "1916.464,884.7" "0.15")
(command "_circle" "1916.089,884.7" "0.15")
(command "_circle" "1917.964,886.7" "0.075")
(command "_circle" "1917.589,886.7" "0.15")
(command "_circle" "1917.214,886.7" "0.075")
(command "_circle" "1916.839,886.7" "0.075")
(command "_circle" "1916.464,886.7" "0.15")
(command "_circle" "1916.089,886.7" "0.15")
(command "_circle" "1917.964,888.7" "0.075")
(command "_circle" "1917.589,888.7" "0.075")
(command "_circle" "1917.214,888.7" "0.15")
(command "_circle" "1916.839,888.7" "0.075")
(command "_circle" "1916.464,888.7" "0.15")
(command "_circle" "1916.089,888.7" "0.15")
(command "_circle" "1917.964,890.7" "0.075")
(command "_circle" "1917.589,890.7" "0.15")
(command "_circle" "1917.214,890.7" "0.15")
(command "_circle" "1916.839,890.7" "0.075")
(command "_circle" "1916.464,890.7" "0.15")
(command "_circle" "1916.089,890.7" "0.15")
(command "_circle" "1917.964,892.7" "0.075")
(command "_circle" "1917.589,892.7" "0.075")
(command "_circle" "1917.214,892.7" "0.075")
(command "_circle" "1916.839,892.7" "0.15")
(command "_circle" "1916.464,892.7" "0.15")
(command "_circle" "1916.089,892.7" "0.15")
(command "_circle" "1917.964,894.7" "0.075")
(command "_circle" "1917.589,894.7" "0.15")
(command "_circle" "1917.214,894.7" "0.075")
(command "_circle" "1916.839,894.7" "0.15")
(command "_circle" "1916.464,894.7" "0.15")
(command "_circle" "1916.089,894.7" "0.15")
(command "_circle" "1917.964,896.7" "0.075")
(command "_circle" "1917.589,896.7" "0.075")
(command "_circle" "1917.214,896.7" "0.15")
(command "_circle" "1916.839,896.7" "0.15")
(command "_circle" "1916.464,896.7" "0.15")
(command "_circle" "1916.089,896.7" "0.15")
(command "_circle" "1917.964,898.7" "0.075")
(command "_circle" "1917.589,898.7" "0.15")
(command "_circle" "1917.214,898.7" "0.15")
(command "_circle" "1916.839,898.7" "0.15")
(command "_circle" "1916.464,898.7" "0.15")
(command "_circle" "1916.089,898.7" "0.15")
(command "_circle" "1917.964,900.7" "0.075")
(command "_circle" "1917.589,900.7" "0.075")
(command "_circle" "1917.214,900.7" "0.075")
(command "_circle" "1916.839,900.7" "0.075")
(command "_circle" "1916.464,900.7" "0.075")
(command "_circle" "1916.089,900.7" "0.075")
(command "_circle" "1915.714,900.7" "0.15")
(command "_circle" "1917.964,902.7" "0.075")
(command "_circle" "1917.589,902.7" "0.15")
(command "_circle" "1917.214,902.7" "0.075")
(command "_circle" "1916.839,902.7" "0.075")
(command "_circle" "1916.464,902.7" "0.075")
(command "_circle" "1916.089,902.7" "0.075")
(command "_circle" "1915.714,902.7" "0.15")
(command "_circle" "1917.964,904.7" "0.075")
(command "_circle" "1917.589,904.7" "0.075")
(command "_circle" "1917.214,904.7" "0.15")
(command "_circle" "1916.839,904.7" "0.075")
(command "_circle" "1916.464,904.7" "0.075")
(command "_circle" "1916.089,904.7" "0.075")
(command "_circle" "1915.714,904.7" "0.15")
(command "_circle" "1917.964,906.7" "0.075")
(command "_circle" "1917.589,906.7" "0.15")
(command "_circle" "1917.214,906.7" "0.15")
(command "_circle" "1916.839,906.7" "0.075")
(command "_circle" "1916.464,906.7" "0.075")
(command "_circle" "1916.089,906.7" "0.075")
(command "_circle" "1915.714,906.7" "0.15")
(command "_circle" "1917.964,908.7" "0.075")
(command "_circle" "1917.589,908.7" "0.075")
(command "_circle" "1917.214,908.7" "0.075")
(command "_circle" "1916.839,908.7" "0.15")
(command "_circle" "1916.464,908.7" "0.075")
(command "_circle" "1916.089,908.7" "0.075")
(command "_circle" "1915.714,908.7" "0.15")
(command "_circle" "1917.964,910.7" "0.075")
(command "_circle" "1917.589,910.7" "0.15")
(command "_circle" "1917.214,910.7" "0.075")
(command "_circle" "1916.839,910.7" "0.15")
(command "_circle" "1916.464,910.7" "0.075")
(command "_circle" "1916.089,910.7" "0.075")
(command "_circle" "1915.714,910.7" "0.15")
(command "_circle" "1917.964,912.7" "0.075")
(command "_circle" "1917.589,912.7" "0.075")
(command "_circle" "1917.214,912.7" "0.15")
(command "_circle" "1916.839,912.7" "0.15")
(command "_circle" "1916.464,912.7" "0.075")
(command "_circle" "1916.089,912.7" "0.075")
(command "_circle" "1915.714,912.7" "0.15")
(command "_circle" "1917.964,914.7" "0.075")
(command "_circle" "1917.589,914.7" "0.15")
(command "_circle" "1917.214,914.7" "0.15")
(command "_circle" "1916.839,914.7" "0.15")
(command "_circle" "1916.464,914.7" "0.075")
(command "_circle" "1916.089,914.7" "0.075")
(command "_circle" "1915.714,914.7" "0.15")
(command "_circle" "1917.964,916.7" "0.075")
(command "_circle" "1917.589,916.7" "0.075")
(command "_circle" "1917.214,916.7" "0.075")
(command "_circle" "1916.839,916.7" "0.075")
(command "_circle" "1916.464,916.7" "0.15")
(command "_circle" "1916.089,916.7" "0.075")
(command "_circle" "1915.714,916.7" "0.15")
(command "_circle" "1917.964,918.7" "0.075")
(command "_circle" "1917.589,918.7" "0.15")
(command "_circle" "1917.214,918.7" "0.075")
(command "_circle" "1916.839,918.7" "0.075")
(command "_circle" "1916.464,918.7" "0.15")
(command "_circle" "1916.089,918.7" "0.075")
(command "_circle" "1915.714,918.7" "0.15")
(command "_circle" "1917.964,920.7" "0.075")
(command "_circle" "1917.589,920.7" "0.075")
(command "_circle" "1917.214,920.7" "0.15")
(command "_circle" "1916.839,920.7" "0.075")
(command "_circle" "1916.464,920.7" "0.15")
(command "_circle" "1916.089,920.7" "0.075")
(command "_circle" "1915.714,920.7" "0.15")
(command "_circle" "1917.964,922.7" "0.075")
(command "_circle" "1917.589,922.7" "0.15")
(command "_circle" "1917.214,922.7" "0.15")
(command "_circle" "1916.839,922.7" "0.075")
(command "_circle" "1916.464,922.7" "0.15")
(command "_circle" "1916.089,922.7" "0.075")
(command "_circle" "1915.714,922.7" "0.15")
(command "_circle" "1917.964,924.7" "0.075")
(command "_circle" "1917.589,924.7" "0.075")
(command "_circle" "1917.214,924.7" "0.075")
(command "_circle" "1916.839,924.7" "0.15")
(command "_circle" "1916.464,924.7" "0.15")
(command "_circle" "1916.089,924.7" "0.075")
(command "_circle" "1915.714,924.7" "0.15")
(command "_circle" "1917.964,926.7" "0.075")
(command "_circle" "1917.589,926.7" "0.15")
(command "_circle" "1917.214,926.7" "0.075")
(command "_circle" "1916.839,926.7" "0.15")
(command "_circle" "1916.464,926.7" "0.15")
(command "_circle" "1916.089,926.7" "0.075")
(command "_circle" "1915.714,926.7" "0.15")
(command "_circle" "1917.964,928.7" "0.075")
(command "_circle" "1917.589,928.7" "0.075")
(command "_circle" "1917.214,928.7" "0.15")
(command "_circle" "1916.839,928.7" "0.15")
(command "_circle" "1916.464,928.7" "0.15")
(command "_circle" "1916.089,928.7" "0.075")
(command "_circle" "1915.714,928.7" "0.15")
(command "_circle" "1917.964,930.7" "0.075")
(command "_circle" "1917.589,930.7" "0.15")
(command "_circle" "1917.214,930.7" "0.15")
(command "_circle" "1916.839,930.7" "0.15")
(command "_circle" "1916.464,930.7" "0.15")
(command "_circle" "1916.089,930.7" "0.075")
(command "_circle" "1915.714,930.7" "0.15")
(command "_circle" "1917.964,932.7" "0.075")
(command "_circle" "1917.589,932.7" "0.075")
(command "_circle" "1917.214,932.7" "0.075")
(command "_circle" "1916.839,932.7" "0.075")
(command "_circle" "1916.464,932.7" "0.075")
(command "_circle" "1916.089,932.7" "0.15")
(command "_circle" "1915.714,932.7" "0.15")
(command "_circle" "1917.964,934.7" "0.075")
(command "_circle" "1917.589,934.7" "0.15")
(command "_circle" "1917.214,934.7" "0.075")
(command "_circle" "1916.839,934.7" "0.075")
(command "_circle" "1916.464,934.7" "0.075")
(command "_circle" "1916.089,934.7" "0.15")
(command "_circle" "1915.714,934.7" "0.15")
(command "_circle" "1917.964,936.7" "0.075")
(command "_circle" "1917.589,936.7" "0.075")
(command "_circle" "1917.214,936.7" "0.15")
(command "_circle" "1916.839,936.7" "0.075")
(command "_circle" "1916.464,936.7" "0.075")
(command "_circle" "1916.089,936.7" "0.15")
(command "_circle" "1915.714,936.7" "0.15")
(command "_circle" "1917.964,938.7" "0.075")
(command "_circle" "1917.589,938.7" "0.15")
(command "_circle" "1917.214,938.7" "0.15")
(command "_circle" "1916.839,938.7" "0.075")
(command "_circle" "1916.464,938.7" "0.075")
(command "_circle" "1916.089,938.7" "0.15")
(command "_circle" "1915.714,938.7" "0.15")
(command "_circle" "1917.964,940.7" "0.075")
(command "_circle" "1917.589,940.7" "0.075")
(command "_circle" "1917.214,940.7" "0.075")
(command "_circle" "1916.839,940.7" "0.15")
(command "_circle" "1916.464,940.7" "0.075")
(command "_circle" "1916.089,940.7" "0.15")
(command "_circle" "1915.714,940.7" "0.15")
(command "_circle" "1917.964,942.7" "0.075")
(command "_circle" "1917.589,942.7" "0.15")
(command "_circle" "1917.214,942.7" "0.075")
(command "_circle" "1916.839,942.7" "0.15")
(command "_circle" "1916.464,942.7" "0.075")
(command "_circle" "1916.089,942.7" "0.15")
(command "_circle" "1915.714,942.7" "0.15")
(command "_circle" "1917.964,944.7" "0.075")
(command "_circle" "1917.589,944.7" "0.075")
(command "_circle" "1917.214,944.7" "0.15")
(command "_circle" "1916.839,944.7" "0.15")
(command "_circle" "1916.464,944.7" "0.075")
(command "_circle" "1916.089,944.7" "0.15")
(command "_circle" "1915.714,944.7" "0.15")
(command "_circle" "1917.964,946.7" "0.075")
(command "_circle" "1917.589,946.7" "0.15")
(command "_circle" "1917.214,946.7" "0.15")
(command "_circle" "1916.839,946.7" "0.15")
(command "_circle" "1916.464,946.7" "0.075")
(command "_circle" "1916.089,946.7" "0.15")
(command "_circle" "1915.714,946.7" "0.15")
(command "_circle" "1917.964,948.7" "0.075")
(command "_circle" "1917.589,948.7" "0.075")
(command "_circle" "1917.214,948.7" "0.075")
(command "_circle" "1916.839,948.7" "0.075")
(command "_circle" "1916.464,948.7" "0.15")
(command "_circle" "1916.089,948.7" "0.15")
(command "_circle" "1915.714,948.7" "0.15")
(command "_circle" "1917.964,950.7" "0.075")
(command "_circle" "1917.589,950.7" "0.15")
(command "_circle" "1917.214,950.7" "0.075")
(command "_circle" "1916.839,950.7" "0.075")
(command "_circle" "1916.464,950.7" "0.15")
(command "_circle" "1916.089,950.7" "0.15")
(command "_circle" "1915.714,950.7" "0.15")
(command "_circle" "1917.964,952.7" "0.075")
(command "_circle" "1917.589,952.7" "0.075")
(command "_circle" "1917.214,952.7" "0.15")
(command "_circle" "1916.839,952.7" "0.075")
(command "_circle" "1916.464,952.7" "0.15")
(command "_circle" "1916.089,952.7" "0.15")
(command "_circle" "1915.714,952.7" "0.15")
(command "_circle" "1917.964,954.7" "0.075")
(command "_circle" "1917.589,954.7" "0.15")
(command "_circle" "1917.214,954.7" "0.15")
(command "_circle" "1916.839,954.7" "0.075")
(command "_circle" "1916.464,954.7" "0.15")
(command "_circle" "1916.089,954.7" "0.15")
(command "_circle" "1915.714,954.7" "0.15")
(command "_circle" "1917.964,956.7" "0.075")
(command "_circle" "1917.589,956.7" "0.075")
(command "_circle" "1917.214,956.7" "0.075")
(command "_circle" "1916.839,956.7" "0.15")
(command "_circle" "1916.464,956.7" "0.15")
(command "_circle" "1916.089,956.7" "0.15")
(command "_circle" "1915.714,956.7" "0.15")
(command "_circle" "1917.964,958.7" "0.075")
(command "_circle" "1917.589,958.7" "0.15")
(command "_circle" "1917.214,958.7" "0.075")
(command "_circle" "1916.839,958.7" "0.15")
(command "_circle" "1916.464,958.7" "0.15")
(command "_circle" "1916.089,958.7" "0.15")
(command "_circle" "1915.714,958.7" "0.15")
(command "_circle" "1917.964,960.7" "0.075")
(command "_circle" "1917.589,960.7" "0.075")
(command "_circle" "1917.214,960.7" "0.15")
(command "_circle" "1916.839,960.7" "0.15")
(command "_circle" "1916.464,960.7" "0.15")
(command "_circle" "1916.089,960.7" "0.15")
(command "_circle" "1915.714,960.7" "0.15")
(command "_circle" "1917.964,962.7" "0.075")
(command "_circle" "1917.589,962.7" "0.15")
(command "_circle" "1917.214,962.7" "0.15")
(command "_circle" "1916.839,962.7" "0.15")
(command "_circle" "1916.464,962.7" "0.15")
(command "_circle" "1916.089,962.7" "0.15")
(command "_circle" "1915.714,962.7" "0.15")
(command "_layer" "set" "nitride" "")
(command "_layer" "set" "text" "")
(command-s "_text" "1906.914,963.3" "2" "-90" "a = 370 nm" )
(sssetfirst nil (ssget "_L"))
(if (not (numberp (vl-string-search "Mac" (getvar "platform")))) (c:txtexp))
(command "_layer" "set" "nitride" "")
(command "_layer" "set" "text" "")
(command-s "_text" "1903.914,963.3" "2" "-90" "gap = 270 nm" )
(sssetfirst nil (ssget "_L"))
(if (not (numberp (vl-string-search "Mac" (getvar "platform")))) (c:txtexp))
(command "_layer" "set" "nitride" "")
(command "_layer" "set" "text" "")
(command-s "_text" "1900.914,963.3" "2" "-90" "amplitude = 127 nm" )
(sssetfirst nil (ssget "_L"))
(if (not (numberp (vl-string-search "Mac" (getvar "platform")))) (c:txtexp))
(command "_layer" "set" "nitride" "")
(command "_layer" "set" "text" "")
(command-s "_text" "1897.914,963.3" "2" "-90" "start width = 280 nm" )
(sssetfirst nil (ssget "_L"))
(if (not (numberp (vl-string-search "Mac" (getvar "platform")))) (c:txtexp))
(command "_layer" "set" "nitride" "")
(command "_layer" "set" "text" "")
(command-s "_text" "1894.914,963.3" "2" "-90" "width = 281 nm" )
(sssetfirst nil (ssget "_L"))
(if (not (numberp (vl-string-search "Mac" (getvar "platform")))) (c:txtexp))
(command "_layer" "set" "nitride" "")
(command "_layer" "set" "text" "")
(command-s "_text" "1891.914,963.3" "2" "-90" "taper: 15" )
(sssetfirst nil (ssget "_L"))
(if (not (numberp (vl-string-search "Mac" (getvar "platform")))) (c:txtexp))
(command "_layer" "set" "nitride" "")
(command "_layer" "set" "text" "")
(command-s "_text" "1888.914,963.3" "2" "-90" "nominal: 150" )
(sssetfirst nil (ssget "_L"))
(if (not (numberp (vl-string-search "Mac" (getvar "platform")))) (c:txtexp))
(command "_layer" "set" "nitride" "")
(command "_layer" "set" "indicators" "")
(setq coords (list 
(list 1840.415 940) 
(list 1840.415 920) 
(list 1820.415 900) 
(list 1840.415 880) 
(list 1840.415 860) 
(list 1840.415 900) 
(list 1840.415 887.0711) 
(list 1827.4861 900) 
(list 1840.415 912.9289) 
(list 1840.415 900)))
(apply 'command (append '("pline") coords '("c")))
(command "._fillet" "radius" "1" "._fillet" "P" (entlast))
(setq coords (list 
(list 1999.585 940) 
(list 1999.585 920) 
(list 2019.585 900) 
(list 1999.585 880) 
(list 1999.585 860) 
(list 1999.585 900) 
(list 1999.585 887.0711) 
(list 2012.5139 900) 
(list 1999.585 912.9289) 
(list 1999.585 900)))
(apply 'command (append '("pline") coords '("c")))
(command "._fillet" "radius" "1" "._fillet" "P" (entlast))
(command "_layer" "set" "holes" "")
(command "_circle" "1838.0629,914.1124" "0.5")
(command "_circle" "1835.7109,911.7603" "0.5")
(command "_circle" "1833.3588,909.4083" "0.5")
(command "_circle" "1831.0067,907.0562" "0.5")
(command "_circle" "1828.6547,904.7041" "0.5")
(command "_circle" "1826.3026,902.3521" "0.5")
(command "_circle" "1823.9505,900" "0.5")
(command "_circle" "1826.3026,897.6479" "0.5")
(command "_circle" "1828.6547,895.2959" "0.5")
(command "_circle" "1831.0067,892.9438" "0.5")
(command "_circle" "1833.3588,890.5917" "0.5")
(command "_circle" "1835.7109,888.2397" "0.5")
(command "_circle" "1838.0629,885.8876" "0.5")
(command "_circle" "2001.9371,914.1124" "0.5")
(command "_circle" "2004.2891,911.7603" "0.5")
(command "_circle" "2006.6412,909.4083" "0.5")
(command "_circle" "2008.9933,907.0562" "0.5")
(command "_circle" "2011.3453,904.7041" "0.5")
(command "_circle" "2013.6974,902.3521" "0.5")
(command "_circle" "2016.0495,900" "0.5")
(command "_circle" "2013.6974,897.6479" "0.5")
(command "_circle" "2011.3453,895.2959" "0.5")
(command "_circle" "2008.9933,892.9438" "0.5")
(command "_circle" "2006.6412,890.5917" "0.5")
(command "_circle" "2004.2891,888.2397" "0.5")
(command "_circle" "2001.9371,885.8876" "0.5")
(command "_layer" "set" "nitride" "")
(command "_block" "blkcoupler6" "1920,900" coupler6 "")
(command "_insert" "blkcoupler6" "1920,900" "1" "1" "0")
(command "_insert" "blkcoupler6" "1920,900" "1" "1" "180")
(command "_block" "blksinglenanobeam6" "1920,900" singlenanobeam6 "")
(command "_insert" "blksinglenanobeam6" "1920,900" "1" "1" "0")
(command "_insert" "blksinglenanobeam6" "1920,900" "1" "1" "180")
(command "_block" "blkanglednodearray6" "1920,900" anglednodearray6 "")
(command "_insert" "blkanglednodearray6" "1920,900" "1" "1" "0")
(command "_insert" "blkanglednodearray6" "1920,900" "1" "1" "180")
(command "_block" "blkcooledsinglenanobeam6" "1920,900" cooledsinglenanobeam6 "")
(command "_insert" "blkcooledsinglenanobeam6" "1920,900" "1" "1" "0")
(command "_insert" "blkcooledsinglenanobeam6" "1920,900" "1" "1" "180")
(command "_block" "blkyjunction6" "1920,900" yjunction6 "")
(command "_insert" "blkyjunction6" "1920,900" "1" "1" "0")
(command "_insert" "blkyjunction6" "1920,900" "1" "1" "180")
; DRAWING BULGING VEE GROOVE
(command "_layer" "set" "vgroove" "")
(setq coords (list 
(list 1845.415 -605) 
(list 1845.415 0) 
(list 1845.415 0) 
(list 1845.415 1800) 
(list 1845.415 1800) 
(list 1845.415 2405) 
(list 1994.585 2405) 
(list 1994.585 1800) 
(list 1994.585 1800) 
(list 1994.585 0) 
(list 1994.585 0) 
(list 1994.585 -605)))
(apply 'command (append '("pline") coords '("c")))
(command "._fillet" "radius" "0" "._fillet" "P" (entlast))
(command "_layer" "set" "window" "")
(command "_rectangle" "1845.415,-1935" "1994.585,-600")
(command "_rectangle" "1845.415,2400" "1994.585,5300")
(command "_layer" "set" "grid" "")
(command "_rectangle" "1846.415,-1934" "1869.9433,-1909.2133")
(command "_array" "last" "" "R" "75" "3" "25.7867" "24.5283")
(command "_rectangle" "1921,-1934" "1944.5283,-1909.2133")
(command "_array" "last" "" "R" "75" "3" "25.7867" "24.5283")
(command "_rectangle" "1846.415,1" "1869.9433,25.7")
(command "_array" "last" "" "R" "70" "3" "25.7" "24.5283")
(command "_rectangle" "1921,1" "1944.5283,25.7")
(command "_array" "last" "" "R" "70" "3" "25.7" "24.5283")
(command "_rectangle" "1846.415,1801" "1869.9433,1825.9185")
(command "_array" "last" "" "R" "135" "3" "25.9185" "24.5283")
(command "_rectangle" "1921,1801" "1944.5283,1825.9185")
(command "_array" "last" "" "R" "135" "3" "25.9185" "24.5283")
(command "_layer" "set" "vgrooveFDA" "")
(command "_rectangle" "1994.585,-2233" "1845.415,-1933")
(command "_layer" "set" "nitride" "")
(command "_layer" "set" "holes" "")
(command "_circle" "1997.085,331.5" "0.5")
(command "_array" "last" "" "R" "379" "1" "3" "2.5")
(command "_circle" "1842.915,331.5" "0.5")
(command "_array" "last" "" "R" "379" "1" "3" "-2.5")
(command "_layer" "set" "nitride" "")
(command "_layer" "set" "window" "")
(command "_layer" "set" "window" "")
(command "_rectangle" "1999.585,0" "2160.415,1800")
(command "._fillet" "radius" "20" "._fillet" "P" (entlast))
(command "_layer" "set" "grid" "")
(command "_rectangle" "2000.585,1" "2022.4179,25.7")
(command "_array" "last" "" "R" "70" "7" "25.7" "22.8329")
(command "_layer" "set" "nitride" "")
; DRAWING REGION LAYER
(command "_layer" "set" "regionLayer6" "")
(command "_rectangle" "1840,-460" "2000,2260")
(command "_layer" "set" "nitride" "")
(setq coupler6 nil)
(setq singlenanobeam6 nil)
(setq anglednodearray6 nil)
(setq cooledsinglenanobeam6 nil)
(setq yjunction6 nil)
; DEVICE #7
(command "_layer" "set" "window" "")
(command "_circle" "2152.915,-415" "5")
(command "_circle" "2152.915,-402.5" "5")
(command "_circle" "2152.915,-390" "5")
(command "_circle" "2152.915,-377.5" "5")
(command "_circle" "2140.415,-415" "5")
(command "_circle" "2140.415,-402.5" "5")
(command "_circle" "2140.415,-390" "5")
(command "_layer" "set" "nitride" "")
(setq currobj nil)
(setq currobj (ssadd))
; DRAWING COUPLER
(setq coords (list 
(list 2240.0615 -415) 
(list 2240.0615 -413) 
(list 2313.585 -413) 
(list 2313.585 -413) 
(list 2313.9677 -413.0761) 
(list 2314.2921 -413.2929) 
(list 2314.5089 -413.6173) 
(list 2314.585 -414) 
(list 2314.585 -411.8) 
(list 2314.585 -411.8) 
(list 2314.5089 -412.1827) 
(list 2314.2921 -412.5071) 
(list 2313.9677 -412.7239) 
(list 2313.585 -412.8) 
(list 2240.0615 -412.8) 
(list 2240.0615 -410.8) 
(list 2239.9385 -410.8) 
(list 2239.9385 -412.8) 
(list 2166.415 -412.8) 
(list 2166.0323 -412.7239) 
(list 2165.7079 -412.5071) 
(list 2165.4911 -412.1827) 
(list 2165.415 -411.8) 
(list 2165.415 -411.8) 
(list 2165.415 -414) 
(list 2165.4911 -413.6173) 
(list 2165.7079 -413.2929) 
(list 2166.0323 -413.0761) 
(list 2166.415 -413) 
(list 2166.415 -413) 
(list 2239.9385 -413) 
(list 2239.9385 -415)))
(apply 'command (append '("pline") coords '("c")))
(setq currobj (ssadd (entlast) currobj))
(command "._fillet" "radius" "0.3" "._fillet" "P" (entlast))
(command "_layer" "set" "holes" "")
(command "_circle" "2240,-412.9" "0.113")
(setq currobj (ssadd (entlast) currobj))
(command "_layer" "set" "nitride" "")
(command "_layer" "set" "text" "")
(command "_circle" "2239.2,-415" "0.075")
(command "_circle" "2239.2,-414.7" "0.075")
(command "_circle" "2239.2,-414.4" "0.075")
(command "_circle" "2238.9,-415" "0.075")
(command "_circle" "2238.9,-414.7" "0.075")
(command "_circle" "2238.9,-414.4" "0.075")
(command "_circle" "2238.6,-415" "0.075")
(command "_circle" "2238.6,-414.7" "0.075")
(command "_circle" "2238.6,-414.4" "0.075")
(command "_layer" "set" "nitride" "")
(command "_layer" "set" "prebias" "")
(command "_rectangle" "2165.415,-414" "2314.585,-411.8")
(setq currobj (ssadd (entlast) currobj))
(command "_rectangle" "2239.9385,-415" "2240.0615,-410.8")
(setq currobj (ssadd (entlast) currobj))
(command "_layer" "set" "nitride" "")
(setq coupler7 currobj)
(setq currobj nil)
(setq currobj (ssadd))
; DRAWING SINGLE NANOBEAM
(setq coords (list 
(list 2240.0615 -410.8) 
(list 2240.0615 -409.1417) 
(list 2240.0615 -407.4833) 
(list 2240.0615 -405.825) 
(list 2240.0615 -404.1667) 
(list 2240.0615 -402.5083) 
(list 2240.0615 -400.85) 
(list 2240.0615 -399.1917) 
(list 2240.0615 -397.5333) 
(list 2240.0616 -395.875) 
(list 2240.0616 -394.2167) 
(list 2240.0616 -392.5583) 
(list 2240.0616 -390.9) 
(list 2240.0617 -389.2417) 
(list 2240.0617 -387.5833) 
(list 2240.0617 -385.925) 
(list 2240.0618 -384.2667) 
(list 2240.0619 -382.6083) 
(list 2240.0619 -380.95) 
(list 2240.062 -379.2917) 
(list 2240.0621 -377.6333) 
(list 2240.0622 -375.975) 
(list 2240.0623 -374.3167) 
(list 2240.0624 -372.6583) 
(list 2240.0625 -371) 
(list 2240.0626 -369.3417) 
(list 2240.0628 -367.6833) 
(list 2240.0629 -366.025) 
(list 2240.0631 -364.3667) 
(list 2240.0632 -362.7083) 
(list 2240.0634 -361.05) 
(list 2240.0636 -359.3917) 
(list 2240.0638 -357.7333) 
(list 2240.0641 -356.075) 
(list 2240.0643 -354.4167) 
(list 2240.0646 -352.7583) 
(list 2240.0648 -351.1) 
(list 2240.0651 -349.4417) 
(list 2240.0654 -347.7833) 
(list 2240.0657 -346.125) 
(list 2240.0661 -344.4667) 
(list 2240.0664 -342.8083) 
(list 2240.0668 -341.15) 
(list 2240.0672 -339.4917) 
(list 2240.0676 -337.8333) 
(list 2240.068 -336.175) 
(list 2240.0685 -334.5167) 
(list 2240.0689 -332.8583) 
(list 2240.0694 -331.2) 
(list 2240.0699 -329.5417) 
(list 2240.0704 -327.8833) 
(list 2240.071 -326.225) 
(list 2240.0715 -324.5667) 
(list 2240.0721 -322.9083) 
(list 2240.0728 -321.25) 
(list 2240.0734 -319.5917) 
(list 2240.0741 -317.9333) 
(list 2240.0747 -316.275) 
(list 2240.0754 -314.6167) 
(list 2240.0762 -312.9583) 
(list 2240.0769 -311.3) 
(list 2240.0777 -309.6417) 
(list 2240.0785 -307.9833) 
(list 2240.0794 -306.325) 
(list 2240.0802 -304.6667) 
(list 2240.0811 -303.0083) 
(list 2240.082 -301.35) 
(list 2240.083 -299.6917) 
(list 2240.084 -298.0333) 
(list 2240.085 -296.375) 
(list 2240.086 -294.7167) 
(list 2240.0871 -293.0583) 
(list 2240.0882 -291.4) 
(list 2240.0893 -289.7417) 
(list 2240.0905 -288.0833) 
(list 2240.0917 -286.425) 
(list 2240.0929 -284.7667) 
(list 2240.0941 -283.1083) 
(list 2240.0954 -281.45) 
(list 2240.0967 -279.7917) 
(list 2240.0981 -278.1333) 
(list 2240.0995 -276.475) 
(list 2240.1009 -274.8167) 
(list 2240.1024 -273.1583) 
(list 2240.1039 -271.5) 
(list 2240.1054 -269.8417) 
(list 2240.107 -268.1833) 
(list 2240.1086 -266.525) 
(list 2240.1102 -264.8667) 
(list 2240.1119 -263.2083) 
(list 2240.1136 -261.55) 
(list 2240.1154 -259.8917) 
(list 2240.1172 -258.2333) 
(list 2240.119 -256.575) 
(list 2240.1209 -254.9167) 
(list 2240.1228 -253.2583) 
(list 2240.1247 -251.6) 
(list 2240.1267 -249.9417) 
(list 2240.1288 -248.2833) 
(list 2240.1308 -246.625) 
(list 2240.133 -244.9667) 
(list 2240.1351 -243.3083) 
(list 2240.1373 -241.65) 
(list 2240.1396 -239.9917) 
(list 2240.1419 -238.3333) 
(list 2240.1442 -236.675) 
(list 2240.1466 -235.0167) 
(list 2240.1491 -233.3583) 
(list 2240.1515 -231.7) 
(list 2240.1541 -230.0417) 
(list 2240.1566 -228.3833) 
(list 2240.1592 -226.725) 
(list 2240.1619 -225.0667) 
(list 2240.1646 -223.4083) 
(list 2240.1674 -221.75) 
(list 2240.1702 -220.0917) 
(list 2240.1731 -218.4333) 
(list 2240.176 -216.775) 
(list 2240.1789 -215.1167) 
(list 2240.1819 -213.4583) 
(list 2240.185 -211.8) 
(list 2239.815 -211.8) 
(list 2239.8181 -213.4583) 
(list 2239.8211 -215.1167) 
(list 2239.824 -216.775) 
(list 2239.8269 -218.4333) 
(list 2239.8298 -220.0917) 
(list 2239.8326 -221.75) 
(list 2239.8354 -223.4083) 
(list 2239.8381 -225.0667) 
(list 2239.8408 -226.725) 
(list 2239.8434 -228.3833) 
(list 2239.8459 -230.0417) 
(list 2239.8485 -231.7) 
(list 2239.8509 -233.3583) 
(list 2239.8534 -235.0167) 
(list 2239.8558 -236.675) 
(list 2239.8581 -238.3333) 
(list 2239.8604 -239.9917) 
(list 2239.8627 -241.65) 
(list 2239.8649 -243.3083) 
(list 2239.867 -244.9667) 
(list 2239.8692 -246.625) 
(list 2239.8712 -248.2833) 
(list 2239.8733 -249.9417) 
(list 2239.8753 -251.6) 
(list 2239.8772 -253.2583) 
(list 2239.8791 -254.9167) 
(list 2239.881 -256.575) 
(list 2239.8828 -258.2333) 
(list 2239.8846 -259.8917) 
(list 2239.8864 -261.55) 
(list 2239.8881 -263.2083) 
(list 2239.8898 -264.8667) 
(list 2239.8914 -266.525) 
(list 2239.893 -268.1833) 
(list 2239.8946 -269.8417) 
(list 2239.8961 -271.5) 
(list 2239.8976 -273.1583) 
(list 2239.8991 -274.8167) 
(list 2239.9005 -276.475) 
(list 2239.9019 -278.1333) 
(list 2239.9033 -279.7917) 
(list 2239.9046 -281.45) 
(list 2239.9059 -283.1083) 
(list 2239.9071 -284.7667) 
(list 2239.9083 -286.425) 
(list 2239.9095 -288.0833) 
(list 2239.9107 -289.7417) 
(list 2239.9118 -291.4) 
(list 2239.9129 -293.0583) 
(list 2239.914 -294.7167) 
(list 2239.915 -296.375) 
(list 2239.916 -298.0333) 
(list 2239.917 -299.6917) 
(list 2239.918 -301.35) 
(list 2239.9189 -303.0083) 
(list 2239.9198 -304.6667) 
(list 2239.9206 -306.325) 
(list 2239.9215 -307.9833) 
(list 2239.9223 -309.6417) 
(list 2239.9231 -311.3) 
(list 2239.9238 -312.9583) 
(list 2239.9246 -314.6167) 
(list 2239.9253 -316.275) 
(list 2239.9259 -317.9333) 
(list 2239.9266 -319.5917) 
(list 2239.9272 -321.25) 
(list 2239.9279 -322.9083) 
(list 2239.9285 -324.5667) 
(list 2239.929 -326.225) 
(list 2239.9296 -327.8833) 
(list 2239.9301 -329.5417) 
(list 2239.9306 -331.2) 
(list 2239.9311 -332.8583) 
(list 2239.9315 -334.5167) 
(list 2239.932 -336.175) 
(list 2239.9324 -337.8333) 
(list 2239.9328 -339.4917) 
(list 2239.9332 -341.15) 
(list 2239.9336 -342.8083) 
(list 2239.9339 -344.4667) 
(list 2239.9343 -346.125) 
(list 2239.9346 -347.7833) 
(list 2239.9349 -349.4417) 
(list 2239.9352 -351.1) 
(list 2239.9354 -352.7583) 
(list 2239.9357 -354.4167) 
(list 2239.9359 -356.075) 
(list 2239.9362 -357.7333) 
(list 2239.9364 -359.3917) 
(list 2239.9366 -361.05) 
(list 2239.9368 -362.7083) 
(list 2239.9369 -364.3667) 
(list 2239.9371 -366.025) 
(list 2239.9372 -367.6833) 
(list 2239.9374 -369.3417) 
(list 2239.9375 -371) 
(list 2239.9376 -372.6583) 
(list 2239.9377 -374.3167) 
(list 2239.9378 -375.975) 
(list 2239.9379 -377.6333) 
(list 2239.938 -379.2917) 
(list 2239.9381 -380.95) 
(list 2239.9381 -382.6083) 
(list 2239.9382 -384.2667) 
(list 2239.9383 -385.925) 
(list 2239.9383 -387.5833) 
(list 2239.9383 -389.2417) 
(list 2239.9384 -390.9) 
(list 2239.9384 -392.5583) 
(list 2239.9384 -394.2167) 
(list 2239.9384 -395.875) 
(list 2239.9385 -397.5333) 
(list 2239.9385 -399.1917) 
(list 2239.9385 -400.85) 
(list 2239.9385 -402.5083) 
(list 2239.9385 -404.1667) 
(list 2239.9385 -405.825) 
(list 2239.9385 -407.4833) 
(list 2239.9385 -409.1417) 
(list 2239.9385 -410.8)))
(apply 'command (append '("pline") coords '("c")))
(setq currobj (ssadd (entlast) currobj))
(command "_layer" "set" "prebias" "")
(command "_rectangle" "2239.815,-410.8" "2240.185,-211.8")
(setq currobj (ssadd (entlast) currobj))
(command "_layer" "set" "nitride" "")
(setq singlenanobeam7 currobj)
(setq currobj nil)
(setq currobj (ssadd))
; DRAWING NODE ARRAY
(setq coords (list 
(list 2240.185 -211.8) 
(list 2240.5625 -201.8) 
(list 2240.5625 -201.8) 
(list 2240.5625 -200.8) 
(list 2314.585 -212.6864) 
(list 2314.585 -207.7434) 
(list 2240.5625 -197.357) 
(list 2240.5625 -196.357) 
(list 2240.5625 -196.357) 
(list 2240.2625 -186.357) 
(list 2239.7375 -186.357) 
(list 2239.4375 -196.357) 
(list 2239.4375 -196.357) 
(list 2239.4375 -197.357) 
(list 2165.415 -207.7434) 
(list 2165.415 -212.6864) 
(list 2239.4375 -200.8) 
(list 2239.4375 -201.8) 
(list 2239.4375 -201.8) 
(list 2239.815 -211.8)))
(apply 'command (append '("pline") coords '("c")))
(setq currobj (ssadd (entlast) currobj))
(command "_layer" "set" "prebias" "")
(setq coords (list 
(list 2239.4375 -212.6864) 
(list 2239.4375 -200.8) 
(list 2165.415 -212.6864) 
(list 2165.415 -207.7434) 
(list 2239.4375 -197.357) 
(list 2239.4375 -186.357) 
(list 2240.5625 -186.357) 
(list 2240.5625 -197.357) 
(list 2314.585 -207.7434) 
(list 2314.585 -212.6864) 
(list 2240.5625 -200.8) 
(list 2240.5625 -212.6864)))
(apply 'command (append '("pline") coords '("c")))
(setq currobj (ssadd (entlast) currobj))
(command "_layer" "set" "nitride" "")
(command "_layer" "set" "fda1" "")
(setq coords (list 
(list 2240.5625 -200.657) 
(list 2314.585 -212.5434) 
(list 2314.585 -212.3664) 
(list 2240.5625 -200.58)))
(apply 'command (append '("pline") coords '("c")))
(setq currobj (ssadd (entlast) currobj))
(setq coords (list 
(list 2240.5625 -200.437) 
(list 2314.585 -212.2234) 
(list 2314.585 -212.0464) 
(list 2240.5625 -200.36)))
(apply 'command (append '("pline") coords '("c")))
(setq currobj (ssadd (entlast) currobj))
(setq coords (list 
(list 2240.5625 -200.217) 
(list 2314.585 -211.9034) 
(list 2314.585 -211.7264) 
(list 2240.5625 -200.14)))
(apply 'command (append '("pline") coords '("c")))
(setq currobj (ssadd (entlast) currobj))
(setq coords (list 
(list 2240.5625 -199.997) 
(list 2314.585 -211.5834) 
(list 2314.585 -211.4064) 
(list 2240.5625 -199.92)))
(apply 'command (append '("pline") coords '("c")))
(setq currobj (ssadd (entlast) currobj))
(setq coords (list 
(list 2240.5625 -199.777) 
(list 2314.585 -211.2634) 
(list 2314.585 -211.0864) 
(list 2240.5625 -199.7)))
(apply 'command (append '("pline") coords '("c")))
(setq currobj (ssadd (entlast) currobj))
(setq coords (list 
(list 2240.5625 -199.557) 
(list 2314.585 -210.9434) 
(list 2314.585 -210.7664) 
(list 2240.5625 -199.48)))
(apply 'command (append '("pline") coords '("c")))
(setq currobj (ssadd (entlast) currobj))
(setq coords (list 
(list 2240.5625 -199.337) 
(list 2314.585 -210.6234) 
(list 2314.585 -210.4464) 
(list 2240.5625 -199.26)))
(apply 'command (append '("pline") coords '("c")))
(setq currobj (ssadd (entlast) currobj))
(setq coords (list 
(list 2240.5625 -199.117) 
(list 2314.585 -210.3034) 
(list 2314.585 -210.1264) 
(list 2240.5625 -199.04)))
(apply 'command (append '("pline") coords '("c")))
(setq currobj (ssadd (entlast) currobj))
(setq coords (list 
(list 2240.5625 -198.897) 
(list 2314.585 -209.9834) 
(list 2314.585 -209.8064) 
(list 2240.5625 -198.82)))
(apply 'command (append '("pline") coords '("c")))
(setq currobj (ssadd (entlast) currobj))
(setq coords (list 
(list 2240.5625 -198.677) 
(list 2314.585 -209.6634) 
(list 2314.585 -209.4864) 
(list 2240.5625 -198.6)))
(apply 'command (append '("pline") coords '("c")))
(setq currobj (ssadd (entlast) currobj))
(setq coords (list 
(list 2240.5625 -198.457) 
(list 2314.585 -209.3434) 
(list 2314.585 -209.1664) 
(list 2240.5625 -198.38)))
(apply 'command (append '("pline") coords '("c")))
(setq currobj (ssadd (entlast) currobj))
(setq coords (list 
(list 2240.5625 -198.237) 
(list 2314.585 -209.0234) 
(list 2314.585 -208.8464) 
(list 2240.5625 -198.16)))
(apply 'command (append '("pline") coords '("c")))
(setq currobj (ssadd (entlast) currobj))
(setq coords (list 
(list 2240.5625 -198.017) 
(list 2314.585 -208.7034) 
(list 2314.585 -208.5264) 
(list 2240.5625 -197.94)))
(apply 'command (append '("pline") coords '("c")))
(setq currobj (ssadd (entlast) currobj))
(setq coords (list 
(list 2240.5625 -197.797) 
(list 2314.585 -208.3834) 
(list 2314.585 -208.2064) 
(list 2240.5625 -197.72)))
(apply 'command (append '("pline") coords '("c")))
(setq currobj (ssadd (entlast) currobj))
(setq coords (list 
(list 2240.5625 -197.577) 
(list 2314.585 -208.0634) 
(list 2314.585 -207.8864) 
(list 2240.5625 -197.5)))
(apply 'command (append '("pline") coords '("c")))
(setq currobj (ssadd (entlast) currobj))
(setq coords (list 
(list 2239.4375 -197.5) 
(list 2165.415 -207.8864) 
(list 2165.415 -208.0634) 
(list 2239.4375 -197.577)))
(apply 'command (append '("pline") coords '("c")))
(setq currobj (ssadd (entlast) currobj))
(setq coords (list 
(list 2239.4375 -197.72) 
(list 2165.415 -208.2064) 
(list 2165.415 -208.3834) 
(list 2239.4375 -197.797)))
(apply 'command (append '("pline") coords '("c")))
(setq currobj (ssadd (entlast) currobj))
(setq coords (list 
(list 2239.4375 -197.94) 
(list 2165.415 -208.5264) 
(list 2165.415 -208.7034) 
(list 2239.4375 -198.017)))
(apply 'command (append '("pline") coords '("c")))
(setq currobj (ssadd (entlast) currobj))
(setq coords (list 
(list 2239.4375 -198.16) 
(list 2165.415 -208.8464) 
(list 2165.415 -209.0234) 
(list 2239.4375 -198.237)))
(apply 'command (append '("pline") coords '("c")))
(setq currobj (ssadd (entlast) currobj))
(setq coords (list 
(list 2239.4375 -198.38) 
(list 2165.415 -209.1664) 
(list 2165.415 -209.3434) 
(list 2239.4375 -198.457)))
(apply 'command (append '("pline") coords '("c")))
(setq currobj (ssadd (entlast) currobj))
(setq coords (list 
(list 2239.4375 -198.6) 
(list 2165.415 -209.4864) 
(list 2165.415 -209.6634) 
(list 2239.4375 -198.677)))
(apply 'command (append '("pline") coords '("c")))
(setq currobj (ssadd (entlast) currobj))
(setq coords (list 
(list 2239.4375 -198.82) 
(list 2165.415 -209.8064) 
(list 2165.415 -209.9834) 
(list 2239.4375 -198.897)))
(apply 'command (append '("pline") coords '("c")))
(setq currobj (ssadd (entlast) currobj))
(setq coords (list 
(list 2239.4375 -199.04) 
(list 2165.415 -210.1264) 
(list 2165.415 -210.3034) 
(list 2239.4375 -199.117)))
(apply 'command (append '("pline") coords '("c")))
(setq currobj (ssadd (entlast) currobj))
(setq coords (list 
(list 2239.4375 -199.26) 
(list 2165.415 -210.4464) 
(list 2165.415 -210.6234) 
(list 2239.4375 -199.337)))
(apply 'command (append '("pline") coords '("c")))
(setq currobj (ssadd (entlast) currobj))
(setq coords (list 
(list 2239.4375 -199.48) 
(list 2165.415 -210.7664) 
(list 2165.415 -210.9434) 
(list 2239.4375 -199.557)))
(apply 'command (append '("pline") coords '("c")))
(setq currobj (ssadd (entlast) currobj))
(setq coords (list 
(list 2239.4375 -199.7) 
(list 2165.415 -211.0864) 
(list 2165.415 -211.2634) 
(list 2239.4375 -199.777)))
(apply 'command (append '("pline") coords '("c")))
(setq currobj (ssadd (entlast) currobj))
(setq coords (list 
(list 2239.4375 -199.92) 
(list 2165.415 -211.4064) 
(list 2165.415 -211.5834) 
(list 2239.4375 -199.997)))
(apply 'command (append '("pline") coords '("c")))
(setq currobj (ssadd (entlast) currobj))
(setq coords (list 
(list 2239.4375 -200.14) 
(list 2165.415 -211.7264) 
(list 2165.415 -211.9034) 
(list 2239.4375 -200.217)))
(apply 'command (append '("pline") coords '("c")))
(setq currobj (ssadd (entlast) currobj))
(setq coords (list 
(list 2239.4375 -200.36) 
(list 2165.415 -212.0464) 
(list 2165.415 -212.2234) 
(list 2239.4375 -200.437)))
(apply 'command (append '("pline") coords '("c")))
(setq currobj (ssadd (entlast) currobj))
(setq coords (list 
(list 2239.4375 -200.58) 
(list 2165.415 -212.3664) 
(list 2165.415 -212.5434) 
(list 2239.4375 -200.657)))
(apply 'command (append '("pline") coords '("c")))
(setq currobj (ssadd (entlast) currobj))
(command "_layer" "set" "nitride" "")
(command "_layer" "set" "text" "")
(command "_circle" "2238.985,-211.8" "0.075")
(command "_circle" "2238.985,-211.5" "0.075")
(command "_circle" "2238.985,-211.2" "0.075")
(command "_circle" "2238.985,-210.9" "0.075")
(command "_circle" "2238.985,-210.6" "0.075")
(command "_circle" "2238.685,-211.8" "0.075")
(command "_circle" "2238.685,-211.5" "0.075")
(command "_circle" "2238.685,-211.2" "0.075")
(command "_circle" "2238.685,-210.9" "0.075")
(command "_circle" "2238.685,-210.6" "0.075")
(command "_circle" "2238.385,-211.8" "0.075")
(command "_circle" "2238.385,-211.5" "0.075")
(command "_circle" "2238.385,-211.2" "0.075")
(command "_circle" "2238.385,-210.9" "0.075")
(command "_circle" "2238.385,-210.6" "0.075")
(command "_circle" "2238.085,-211.8" "0.075")
(command "_circle" "2238.085,-211.5" "0.075")
(command "_circle" "2238.085,-211.2" "0.075")
(command "_circle" "2238.085,-210.9" "0.075")
(command "_circle" "2238.085,-210.6" "0.075")
(command "_circle" "2237.785,-211.8" "0.075")
(command "_circle" "2237.785,-211.5" "0.075")
(command "_circle" "2237.785,-211.2" "0.075")
(command "_circle" "2237.785,-210.9" "0.075")
(command "_circle" "2237.785,-210.6" "0.075")
(command "_layer" "set" "nitride" "")
(setq anglednodearray7 currobj)
(setq currobj nil)
(setq currobj (ssadd))
; DRAWING COOLED SINGLE NANOBEAM
(setq coords (list 
(list 2240.2625 -186.357) 
(list 2240.2625 -181.357) 
(list 2239.7375 -181.357) 
(list 2239.7375 -186.357)))
(apply 'command (append '("pline") coords '("c")))
(setq currobj (ssadd (entlast) currobj))
(command "_layer" "set" "prebias" "")
(command "_rectangle" "2239.7375,-186.357" "2240.2625,-181.357")
(setq currobj (ssadd (entlast) currobj))
(command "_layer" "set" "nitride" "")
(setq coords (list 
(list 2240.2625 -181.357) 
(list 2240.5625 -171.357) 
(list 2240.5625 -171.357) 
(list 2240.5625 -170.357) 
(list 2314.585 -171.107) 
(list 2314.585 -166.164) 
(list 2240.5625 -166.914) 
(list 2240.5625 -165.914) 
(list 2240.5625 -165.914) 
(list 2240.2625 -155.914) 
(list 2239.7375 -155.914) 
(list 2239.4375 -165.914) 
(list 2239.4375 -165.914) 
(list 2239.4375 -166.914) 
(list 2165.415 -166.164) 
(list 2165.415 -171.107) 
(list 2239.4375 -170.357) 
(list 2239.4375 -171.357) 
(list 2239.4375 -171.357) 
(list 2239.7375 -181.357)))
(apply 'command (append '("pline") coords '("c")))
(setq currobj (ssadd (entlast) currobj))
(command "_layer" "set" "prebias" "")
(setq coords (list 
(list 2239.4375 -181.357) 
(list 2239.4375 -170.357) 
(list 2165.415 -171.107) 
(list 2165.415 -166.164) 
(list 2239.4375 -166.914) 
(list 2239.4375 -155.914) 
(list 2240.5625 -155.914) 
(list 2240.5625 -166.914) 
(list 2314.585 -166.164) 
(list 2314.585 -171.107) 
(list 2240.5625 -170.357) 
(list 2240.5625 -181.357)))
(apply 'command (append '("pline") coords '("c")))
(setq currobj (ssadd (entlast) currobj))
(command "_layer" "set" "nitride" "")
(command "_layer" "set" "fda1" "")
(setq coords (list 
(list 2240.5625 -170.214) 
(list 2314.585 -170.964) 
(list 2314.585 -170.787) 
(list 2240.5625 -170.137)))
(apply 'command (append '("pline") coords '("c")))
(setq currobj (ssadd (entlast) currobj))
(setq coords (list 
(list 2240.5625 -169.994) 
(list 2314.585 -170.644) 
(list 2314.585 -170.467) 
(list 2240.5625 -169.917)))
(apply 'command (append '("pline") coords '("c")))
(setq currobj (ssadd (entlast) currobj))
(setq coords (list 
(list 2240.5625 -169.774) 
(list 2314.585 -170.324) 
(list 2314.585 -170.147) 
(list 2240.5625 -169.697)))
(apply 'command (append '("pline") coords '("c")))
(setq currobj (ssadd (entlast) currobj))
(setq coords (list 
(list 2240.5625 -169.554) 
(list 2314.585 -170.004) 
(list 2314.585 -169.827) 
(list 2240.5625 -169.477)))
(apply 'command (append '("pline") coords '("c")))
(setq currobj (ssadd (entlast) currobj))
(setq coords (list 
(list 2240.5625 -169.334) 
(list 2314.585 -169.684) 
(list 2314.585 -169.507) 
(list 2240.5625 -169.257)))
(apply 'command (append '("pline") coords '("c")))
(setq currobj (ssadd (entlast) currobj))
(setq coords (list 
(list 2240.5625 -169.114) 
(list 2314.585 -169.364) 
(list 2314.585 -169.187) 
(list 2240.5625 -169.037)))
(apply 'command (append '("pline") coords '("c")))
(setq currobj (ssadd (entlast) currobj))
(setq coords (list 
(list 2240.5625 -168.894) 
(list 2314.585 -169.044) 
(list 2314.585 -168.867) 
(list 2240.5625 -168.817)))
(apply 'command (append '("pline") coords '("c")))
(setq currobj (ssadd (entlast) currobj))
(setq coords (list 
(list 2240.5625 -168.674) 
(list 2314.585 -168.724) 
(list 2314.585 -168.547) 
(list 2240.5625 -168.597)))
(apply 'command (append '("pline") coords '("c")))
(setq currobj (ssadd (entlast) currobj))
(setq coords (list 
(list 2240.5625 -168.454) 
(list 2314.585 -168.404) 
(list 2314.585 -168.227) 
(list 2240.5625 -168.377)))
(apply 'command (append '("pline") coords '("c")))
(setq currobj (ssadd (entlast) currobj))
(setq coords (list 
(list 2240.5625 -168.234) 
(list 2314.585 -168.084) 
(list 2314.585 -167.907) 
(list 2240.5625 -168.157)))
(apply 'command (append '("pline") coords '("c")))
(setq currobj (ssadd (entlast) currobj))
(setq coords (list 
(list 2240.5625 -168.014) 
(list 2314.585 -167.764) 
(list 2314.585 -167.587) 
(list 2240.5625 -167.937)))
(apply 'command (append '("pline") coords '("c")))
(setq currobj (ssadd (entlast) currobj))
(setq coords (list 
(list 2240.5625 -167.794) 
(list 2314.585 -167.444) 
(list 2314.585 -167.267) 
(list 2240.5625 -167.717)))
(apply 'command (append '("pline") coords '("c")))
(setq currobj (ssadd (entlast) currobj))
(setq coords (list 
(list 2240.5625 -167.574) 
(list 2314.585 -167.124) 
(list 2314.585 -166.947) 
(list 2240.5625 -167.497)))
(apply 'command (append '("pline") coords '("c")))
(setq currobj (ssadd (entlast) currobj))
(setq coords (list 
(list 2240.5625 -167.354) 
(list 2314.585 -166.804) 
(list 2314.585 -166.627) 
(list 2240.5625 -167.277)))
(apply 'command (append '("pline") coords '("c")))
(setq currobj (ssadd (entlast) currobj))
(setq coords (list 
(list 2240.5625 -167.134) 
(list 2314.585 -166.484) 
(list 2314.585 -166.307) 
(list 2240.5625 -167.057)))
(apply 'command (append '("pline") coords '("c")))
(setq currobj (ssadd (entlast) currobj))
(setq coords (list 
(list 2239.4375 -167.057) 
(list 2165.415 -166.307) 
(list 2165.415 -166.484) 
(list 2239.4375 -167.134)))
(apply 'command (append '("pline") coords '("c")))
(setq currobj (ssadd (entlast) currobj))
(setq coords (list 
(list 2239.4375 -167.277) 
(list 2165.415 -166.627) 
(list 2165.415 -166.804) 
(list 2239.4375 -167.354)))
(apply 'command (append '("pline") coords '("c")))
(setq currobj (ssadd (entlast) currobj))
(setq coords (list 
(list 2239.4375 -167.497) 
(list 2165.415 -166.947) 
(list 2165.415 -167.124) 
(list 2239.4375 -167.574)))
(apply 'command (append '("pline") coords '("c")))
(setq currobj (ssadd (entlast) currobj))
(setq coords (list 
(list 2239.4375 -167.717) 
(list 2165.415 -167.267) 
(list 2165.415 -167.444) 
(list 2239.4375 -167.794)))
(apply 'command (append '("pline") coords '("c")))
(setq currobj (ssadd (entlast) currobj))
(setq coords (list 
(list 2239.4375 -167.937) 
(list 2165.415 -167.587) 
(list 2165.415 -167.764) 
(list 2239.4375 -168.014)))
(apply 'command (append '("pline") coords '("c")))
(setq currobj (ssadd (entlast) currobj))
(setq coords (list 
(list 2239.4375 -168.157) 
(list 2165.415 -167.907) 
(list 2165.415 -168.084) 
(list 2239.4375 -168.234)))
(apply 'command (append '("pline") coords '("c")))
(setq currobj (ssadd (entlast) currobj))
(setq coords (list 
(list 2239.4375 -168.377) 
(list 2165.415 -168.227) 
(list 2165.415 -168.404) 
(list 2239.4375 -168.454)))
(apply 'command (append '("pline") coords '("c")))
(setq currobj (ssadd (entlast) currobj))
(setq coords (list 
(list 2239.4375 -168.597) 
(list 2165.415 -168.547) 
(list 2165.415 -168.724) 
(list 2239.4375 -168.674)))
(apply 'command (append '("pline") coords '("c")))
(setq currobj (ssadd (entlast) currobj))
(setq coords (list 
(list 2239.4375 -168.817) 
(list 2165.415 -168.867) 
(list 2165.415 -169.044) 
(list 2239.4375 -168.894)))
(apply 'command (append '("pline") coords '("c")))
(setq currobj (ssadd (entlast) currobj))
(setq coords (list 
(list 2239.4375 -169.037) 
(list 2165.415 -169.187) 
(list 2165.415 -169.364) 
(list 2239.4375 -169.114)))
(apply 'command (append '("pline") coords '("c")))
(setq currobj (ssadd (entlast) currobj))
(setq coords (list 
(list 2239.4375 -169.257) 
(list 2165.415 -169.507) 
(list 2165.415 -169.684) 
(list 2239.4375 -169.334)))
(apply 'command (append '("pline") coords '("c")))
(setq currobj (ssadd (entlast) currobj))
(setq coords (list 
(list 2239.4375 -169.477) 
(list 2165.415 -169.827) 
(list 2165.415 -170.004) 
(list 2239.4375 -169.554)))
(apply 'command (append '("pline") coords '("c")))
(setq currobj (ssadd (entlast) currobj))
(setq coords (list 
(list 2239.4375 -169.697) 
(list 2165.415 -170.147) 
(list 2165.415 -170.324) 
(list 2239.4375 -169.774)))
(apply 'command (append '("pline") coords '("c")))
(setq currobj (ssadd (entlast) currobj))
(setq coords (list 
(list 2239.4375 -169.917) 
(list 2165.415 -170.467) 
(list 2165.415 -170.644) 
(list 2239.4375 -169.994)))
(apply 'command (append '("pline") coords '("c")))
(setq currobj (ssadd (entlast) currobj))
(setq coords (list 
(list 2239.4375 -170.137) 
(list 2165.415 -170.787) 
(list 2165.415 -170.964) 
(list 2239.4375 -170.214)))
(apply 'command (append '("pline") coords '("c")))
(setq currobj (ssadd (entlast) currobj))
(command "_layer" "set" "nitride" "")
(command "_layer" "set" "text" "")
(command "_circle" "2239.0625,-181.357" "0.075")
(command "_circle" "2239.0625,-181.057" "0.075")
(command "_circle" "2239.0625,-180.757" "0.075")
(command "_circle" "2239.0625,-180.457" "0.075")
(command "_circle" "2239.0625,-180.157" "0.075")
(command "_circle" "2238.7625,-181.357" "0.075")
(command "_circle" "2238.7625,-181.057" "0.075")
(command "_circle" "2238.7625,-180.757" "0.075")
(command "_circle" "2238.7625,-180.457" "0.075")
(command "_circle" "2238.7625,-180.157" "0.075")
(command "_circle" "2238.4625,-181.357" "0.075")
(command "_circle" "2238.4625,-181.057" "0.075")
(command "_circle" "2238.4625,-180.757" "0.075")
(command "_circle" "2238.4625,-180.457" "0.075")
(command "_circle" "2238.4625,-180.157" "0.075")
(command "_circle" "2238.1625,-181.357" "0.075")
(command "_circle" "2238.1625,-181.057" "0.075")
(command "_circle" "2238.1625,-180.757" "0.075")
(command "_circle" "2238.1625,-180.457" "0.075")
(command "_circle" "2238.1625,-180.157" "0.075")
(command "_circle" "2237.8625,-181.357" "0.075")
(command "_circle" "2237.8625,-181.057" "0.075")
(command "_circle" "2237.8625,-180.757" "0.075")
(command "_circle" "2237.8625,-180.457" "0.075")
(command "_circle" "2237.8625,-180.157" "0.075")
(command "_layer" "set" "nitride" "")
(setq coords (list 
(list 2240.2625 -155.914) 
(list 2240.2625 -40.2693) 
(list 2239.7375 -40.2693) 
(list 2239.7375 -155.914)))
(apply 'command (append '("pline") coords '("c")))
(setq currobj (ssadd (entlast) currobj))
(command "_layer" "set" "prebias" "")
(command "_rectangle" "2239.7375,-155.914" "2240.2625,-40.2693")
(setq currobj (ssadd (entlast) currobj))
(command "_layer" "set" "nitride" "")
(setq coords (list 
(list 2240.2625 -40.2693) 
(list 2240.5625 -30.2693) 
(list 2240.5625 -30.2693) 
(list 2240.5625 -29.2693) 
(list 2314.585 -30.0193) 
(list 2314.585 -25.0763) 
(list 2240.5625 -25.8263) 
(list 2240.5625 -24.8263) 
(list 2240.5625 -24.8263) 
(list 2240.2625 -14.8263) 
(list 2239.7375 -14.8263) 
(list 2239.4375 -24.8263) 
(list 2239.4375 -24.8263) 
(list 2239.4375 -25.8263) 
(list 2165.415 -25.0763) 
(list 2165.415 -30.0193) 
(list 2239.4375 -29.2693) 
(list 2239.4375 -30.2693) 
(list 2239.4375 -30.2693) 
(list 2239.7375 -40.2693)))
(apply 'command (append '("pline") coords '("c")))
(setq currobj (ssadd (entlast) currobj))
(command "_layer" "set" "prebias" "")
(setq coords (list 
(list 2239.4375 -40.2693) 
(list 2239.4375 -29.2693) 
(list 2165.415 -30.0193) 
(list 2165.415 -25.0763) 
(list 2239.4375 -25.8263) 
(list 2239.4375 -14.8263) 
(list 2240.5625 -14.8263) 
(list 2240.5625 -25.8263) 
(list 2314.585 -25.0763) 
(list 2314.585 -30.0193) 
(list 2240.5625 -29.2693) 
(list 2240.5625 -40.2693)))
(apply 'command (append '("pline") coords '("c")))
(setq currobj (ssadd (entlast) currobj))
(command "_layer" "set" "nitride" "")
(command "_layer" "set" "fda1" "")
(setq coords (list 
(list 2240.5625 -29.1263) 
(list 2314.585 -29.8763) 
(list 2314.585 -29.6993) 
(list 2240.5625 -29.0493)))
(apply 'command (append '("pline") coords '("c")))
(setq currobj (ssadd (entlast) currobj))
(setq coords (list 
(list 2240.5625 -28.9063) 
(list 2314.585 -29.5563) 
(list 2314.585 -29.3793) 
(list 2240.5625 -28.8293)))
(apply 'command (append '("pline") coords '("c")))
(setq currobj (ssadd (entlast) currobj))
(setq coords (list 
(list 2240.5625 -28.6863) 
(list 2314.585 -29.2363) 
(list 2314.585 -29.0593) 
(list 2240.5625 -28.6093)))
(apply 'command (append '("pline") coords '("c")))
(setq currobj (ssadd (entlast) currobj))
(setq coords (list 
(list 2240.5625 -28.4663) 
(list 2314.585 -28.9163) 
(list 2314.585 -28.7393) 
(list 2240.5625 -28.3893)))
(apply 'command (append '("pline") coords '("c")))
(setq currobj (ssadd (entlast) currobj))
(setq coords (list 
(list 2240.5625 -28.2463) 
(list 2314.585 -28.5963) 
(list 2314.585 -28.4193) 
(list 2240.5625 -28.1693)))
(apply 'command (append '("pline") coords '("c")))
(setq currobj (ssadd (entlast) currobj))
(setq coords (list 
(list 2240.5625 -28.0263) 
(list 2314.585 -28.2763) 
(list 2314.585 -28.0993) 
(list 2240.5625 -27.9493)))
(apply 'command (append '("pline") coords '("c")))
(setq currobj (ssadd (entlast) currobj))
(setq coords (list 
(list 2240.5625 -27.8063) 
(list 2314.585 -27.9563) 
(list 2314.585 -27.7793) 
(list 2240.5625 -27.7293)))
(apply 'command (append '("pline") coords '("c")))
(setq currobj (ssadd (entlast) currobj))
(setq coords (list 
(list 2240.5625 -27.5863) 
(list 2314.585 -27.6363) 
(list 2314.585 -27.4593) 
(list 2240.5625 -27.5093)))
(apply 'command (append '("pline") coords '("c")))
(setq currobj (ssadd (entlast) currobj))
(setq coords (list 
(list 2240.5625 -27.3663) 
(list 2314.585 -27.3163) 
(list 2314.585 -27.1393) 
(list 2240.5625 -27.2893)))
(apply 'command (append '("pline") coords '("c")))
(setq currobj (ssadd (entlast) currobj))
(setq coords (list 
(list 2240.5625 -27.1463) 
(list 2314.585 -26.9963) 
(list 2314.585 -26.8193) 
(list 2240.5625 -27.0693)))
(apply 'command (append '("pline") coords '("c")))
(setq currobj (ssadd (entlast) currobj))
(setq coords (list 
(list 2240.5625 -26.9263) 
(list 2314.585 -26.6763) 
(list 2314.585 -26.4993) 
(list 2240.5625 -26.8493)))
(apply 'command (append '("pline") coords '("c")))
(setq currobj (ssadd (entlast) currobj))
(setq coords (list 
(list 2240.5625 -26.7063) 
(list 2314.585 -26.3563) 
(list 2314.585 -26.1793) 
(list 2240.5625 -26.6293)))
(apply 'command (append '("pline") coords '("c")))
(setq currobj (ssadd (entlast) currobj))
(setq coords (list 
(list 2240.5625 -26.4863) 
(list 2314.585 -26.0363) 
(list 2314.585 -25.8593) 
(list 2240.5625 -26.4093)))
(apply 'command (append '("pline") coords '("c")))
(setq currobj (ssadd (entlast) currobj))
(setq coords (list 
(list 2240.5625 -26.2663) 
(list 2314.585 -25.7163) 
(list 2314.585 -25.5393) 
(list 2240.5625 -26.1893)))
(apply 'command (append '("pline") coords '("c")))
(setq currobj (ssadd (entlast) currobj))
(setq coords (list 
(list 2240.5625 -26.0463) 
(list 2314.585 -25.3963) 
(list 2314.585 -25.2193) 
(list 2240.5625 -25.9693)))
(apply 'command (append '("pline") coords '("c")))
(setq currobj (ssadd (entlast) currobj))
(setq coords (list 
(list 2239.4375 -25.9693) 
(list 2165.415 -25.2193) 
(list 2165.415 -25.3963) 
(list 2239.4375 -26.0463)))
(apply 'command (append '("pline") coords '("c")))
(setq currobj (ssadd (entlast) currobj))
(setq coords (list 
(list 2239.4375 -26.1893) 
(list 2165.415 -25.5393) 
(list 2165.415 -25.7163) 
(list 2239.4375 -26.2663)))
(apply 'command (append '("pline") coords '("c")))
(setq currobj (ssadd (entlast) currobj))
(setq coords (list 
(list 2239.4375 -26.4093) 
(list 2165.415 -25.8593) 
(list 2165.415 -26.0363) 
(list 2239.4375 -26.4863)))
(apply 'command (append '("pline") coords '("c")))
(setq currobj (ssadd (entlast) currobj))
(setq coords (list 
(list 2239.4375 -26.6293) 
(list 2165.415 -26.1793) 
(list 2165.415 -26.3563) 
(list 2239.4375 -26.7063)))
(apply 'command (append '("pline") coords '("c")))
(setq currobj (ssadd (entlast) currobj))
(setq coords (list 
(list 2239.4375 -26.8493) 
(list 2165.415 -26.4993) 
(list 2165.415 -26.6763) 
(list 2239.4375 -26.9263)))
(apply 'command (append '("pline") coords '("c")))
(setq currobj (ssadd (entlast) currobj))
(setq coords (list 
(list 2239.4375 -27.0693) 
(list 2165.415 -26.8193) 
(list 2165.415 -26.9963) 
(list 2239.4375 -27.1463)))
(apply 'command (append '("pline") coords '("c")))
(setq currobj (ssadd (entlast) currobj))
(setq coords (list 
(list 2239.4375 -27.2893) 
(list 2165.415 -27.1393) 
(list 2165.415 -27.3163) 
(list 2239.4375 -27.3663)))
(apply 'command (append '("pline") coords '("c")))
(setq currobj (ssadd (entlast) currobj))
(setq coords (list 
(list 2239.4375 -27.5093) 
(list 2165.415 -27.4593) 
(list 2165.415 -27.6363) 
(list 2239.4375 -27.5863)))
(apply 'command (append '("pline") coords '("c")))
(setq currobj (ssadd (entlast) currobj))
(setq coords (list 
(list 2239.4375 -27.7293) 
(list 2165.415 -27.7793) 
(list 2165.415 -27.9563) 
(list 2239.4375 -27.8063)))
(apply 'command (append '("pline") coords '("c")))
(setq currobj (ssadd (entlast) currobj))
(setq coords (list 
(list 2239.4375 -27.9493) 
(list 2165.415 -28.0993) 
(list 2165.415 -28.2763) 
(list 2239.4375 -28.0263)))
(apply 'command (append '("pline") coords '("c")))
(setq currobj (ssadd (entlast) currobj))
(setq coords (list 
(list 2239.4375 -28.1693) 
(list 2165.415 -28.4193) 
(list 2165.415 -28.5963) 
(list 2239.4375 -28.2463)))
(apply 'command (append '("pline") coords '("c")))
(setq currobj (ssadd (entlast) currobj))
(setq coords (list 
(list 2239.4375 -28.3893) 
(list 2165.415 -28.7393) 
(list 2165.415 -28.9163) 
(list 2239.4375 -28.4663)))
(apply 'command (append '("pline") coords '("c")))
(setq currobj (ssadd (entlast) currobj))
(setq coords (list 
(list 2239.4375 -28.6093) 
(list 2165.415 -29.0593) 
(list 2165.415 -29.2363) 
(list 2239.4375 -28.6863)))
(apply 'command (append '("pline") coords '("c")))
(setq currobj (ssadd (entlast) currobj))
(setq coords (list 
(list 2239.4375 -28.8293) 
(list 2165.415 -29.3793) 
(list 2165.415 -29.5563) 
(list 2239.4375 -28.9063)))
(apply 'command (append '("pline") coords '("c")))
(setq currobj (ssadd (entlast) currobj))
(setq coords (list 
(list 2239.4375 -29.0493) 
(list 2165.415 -29.6993) 
(list 2165.415 -29.8763) 
(list 2239.4375 -29.1263)))
(apply 'command (append '("pline") coords '("c")))
(setq currobj (ssadd (entlast) currobj))
(command "_layer" "set" "nitride" "")
(command "_layer" "set" "text" "")
(command "_circle" "2239.0625,-40.2693" "0.075")
(command "_circle" "2239.0625,-39.9693" "0.075")
(command "_circle" "2239.0625,-39.6693" "0.075")
(command "_circle" "2239.0625,-39.3693" "0.075")
(command "_circle" "2239.0625,-39.0693" "0.075")
(command "_circle" "2238.7625,-40.2693" "0.075")
(command "_circle" "2238.7625,-39.9693" "0.075")
(command "_circle" "2238.7625,-39.6693" "0.075")
(command "_circle" "2238.7625,-39.3693" "0.075")
(command "_circle" "2238.7625,-39.0693" "0.075")
(command "_circle" "2238.4625,-40.2693" "0.075")
(command "_circle" "2238.4625,-39.9693" "0.075")
(command "_circle" "2238.4625,-39.6693" "0.075")
(command "_circle" "2238.4625,-39.3693" "0.075")
(command "_circle" "2238.4625,-39.0693" "0.075")
(command "_circle" "2238.1625,-40.2693" "0.075")
(command "_circle" "2238.1625,-39.9693" "0.075")
(command "_circle" "2238.1625,-39.6693" "0.075")
(command "_circle" "2238.1625,-39.3693" "0.075")
(command "_circle" "2238.1625,-39.0693" "0.075")
(command "_circle" "2237.8625,-40.2693" "0.075")
(command "_circle" "2237.8625,-39.9693" "0.075")
(command "_circle" "2237.8625,-39.6693" "0.075")
(command "_circle" "2237.8625,-39.3693" "0.075")
(command "_circle" "2237.8625,-39.0693" "0.075")
(command "_layer" "set" "nitride" "")
(setq coords (list 
(list 2240.2625 -14.8263) 
(list 2240.2625 100.8184) 
(list 2239.7375 100.8184) 
(list 2239.7375 -14.8263)))
(apply 'command (append '("pline") coords '("c")))
(setq currobj (ssadd (entlast) currobj))
(command "_layer" "set" "prebias" "")
(command "_rectangle" "2239.7375,-14.8263" "2240.2625,100.8184")
(setq currobj (ssadd (entlast) currobj))
(command "_layer" "set" "nitride" "")
(setq coords (list 
(list 2240.2625 100.8184) 
(list 2240.5625 110.8184) 
(list 2240.5625 110.8184) 
(list 2240.5625 111.8184) 
(list 2314.585 111.0684) 
(list 2314.585 116.0114) 
(list 2240.5625 115.2614) 
(list 2240.5625 116.2614) 
(list 2240.5625 116.2614) 
(list 2240.2625 126.2614) 
(list 2239.7375 126.2614) 
(list 2239.4375 116.2614) 
(list 2239.4375 116.2614) 
(list 2239.4375 115.2614) 
(list 2165.415 116.0114) 
(list 2165.415 111.0684) 
(list 2239.4375 111.8184) 
(list 2239.4375 110.8184) 
(list 2239.4375 110.8184) 
(list 2239.7375 100.8184)))
(apply 'command (append '("pline") coords '("c")))
(setq currobj (ssadd (entlast) currobj))
(command "_layer" "set" "prebias" "")
(setq coords (list 
(list 2239.4375 100.8184) 
(list 2239.4375 111.8184) 
(list 2165.415 111.0684) 
(list 2165.415 116.0114) 
(list 2239.4375 115.2614) 
(list 2239.4375 126.2614) 
(list 2240.5625 126.2614) 
(list 2240.5625 115.2614) 
(list 2314.585 116.0114) 
(list 2314.585 111.0684) 
(list 2240.5625 111.8184) 
(list 2240.5625 100.8184)))
(apply 'command (append '("pline") coords '("c")))
(setq currobj (ssadd (entlast) currobj))
(command "_layer" "set" "nitride" "")
(command "_layer" "set" "fda1" "")
(setq coords (list 
(list 2240.5625 111.9614) 
(list 2314.585 111.2114) 
(list 2314.585 111.3884) 
(list 2240.5625 112.0384)))
(apply 'command (append '("pline") coords '("c")))
(setq currobj (ssadd (entlast) currobj))
(setq coords (list 
(list 2240.5625 112.1814) 
(list 2314.585 111.5314) 
(list 2314.585 111.7084) 
(list 2240.5625 112.2584)))
(apply 'command (append '("pline") coords '("c")))
(setq currobj (ssadd (entlast) currobj))
(setq coords (list 
(list 2240.5625 112.4014) 
(list 2314.585 111.8514) 
(list 2314.585 112.0284) 
(list 2240.5625 112.4784)))
(apply 'command (append '("pline") coords '("c")))
(setq currobj (ssadd (entlast) currobj))
(setq coords (list 
(list 2240.5625 112.6214) 
(list 2314.585 112.1714) 
(list 2314.585 112.3484) 
(list 2240.5625 112.6984)))
(apply 'command (append '("pline") coords '("c")))
(setq currobj (ssadd (entlast) currobj))
(setq coords (list 
(list 2240.5625 112.8414) 
(list 2314.585 112.4914) 
(list 2314.585 112.6684) 
(list 2240.5625 112.9184)))
(apply 'command (append '("pline") coords '("c")))
(setq currobj (ssadd (entlast) currobj))
(setq coords (list 
(list 2240.5625 113.0614) 
(list 2314.585 112.8114) 
(list 2314.585 112.9884) 
(list 2240.5625 113.1384)))
(apply 'command (append '("pline") coords '("c")))
(setq currobj (ssadd (entlast) currobj))
(setq coords (list 
(list 2240.5625 113.2814) 
(list 2314.585 113.1314) 
(list 2314.585 113.3084) 
(list 2240.5625 113.3584)))
(apply 'command (append '("pline") coords '("c")))
(setq currobj (ssadd (entlast) currobj))
(setq coords (list 
(list 2240.5625 113.5014) 
(list 2314.585 113.4514) 
(list 2314.585 113.6284) 
(list 2240.5625 113.5784)))
(apply 'command (append '("pline") coords '("c")))
(setq currobj (ssadd (entlast) currobj))
(setq coords (list 
(list 2240.5625 113.7214) 
(list 2314.585 113.7714) 
(list 2314.585 113.9484) 
(list 2240.5625 113.7984)))
(apply 'command (append '("pline") coords '("c")))
(setq currobj (ssadd (entlast) currobj))
(setq coords (list 
(list 2240.5625 113.9414) 
(list 2314.585 114.0914) 
(list 2314.585 114.2684) 
(list 2240.5625 114.0184)))
(apply 'command (append '("pline") coords '("c")))
(setq currobj (ssadd (entlast) currobj))
(setq coords (list 
(list 2240.5625 114.1614) 
(list 2314.585 114.4114) 
(list 2314.585 114.5884) 
(list 2240.5625 114.2384)))
(apply 'command (append '("pline") coords '("c")))
(setq currobj (ssadd (entlast) currobj))
(setq coords (list 
(list 2240.5625 114.3814) 
(list 2314.585 114.7314) 
(list 2314.585 114.9084) 
(list 2240.5625 114.4584)))
(apply 'command (append '("pline") coords '("c")))
(setq currobj (ssadd (entlast) currobj))
(setq coords (list 
(list 2240.5625 114.6014) 
(list 2314.585 115.0514) 
(list 2314.585 115.2284) 
(list 2240.5625 114.6784)))
(apply 'command (append '("pline") coords '("c")))
(setq currobj (ssadd (entlast) currobj))
(setq coords (list 
(list 2240.5625 114.8214) 
(list 2314.585 115.3714) 
(list 2314.585 115.5484) 
(list 2240.5625 114.8984)))
(apply 'command (append '("pline") coords '("c")))
(setq currobj (ssadd (entlast) currobj))
(setq coords (list 
(list 2240.5625 115.0414) 
(list 2314.585 115.6914) 
(list 2314.585 115.8684) 
(list 2240.5625 115.1184)))
(apply 'command (append '("pline") coords '("c")))
(setq currobj (ssadd (entlast) currobj))
(setq coords (list 
(list 2239.4375 115.1184) 
(list 2165.415 115.8684) 
(list 2165.415 115.6914) 
(list 2239.4375 115.0414)))
(apply 'command (append '("pline") coords '("c")))
(setq currobj (ssadd (entlast) currobj))
(setq coords (list 
(list 2239.4375 114.8984) 
(list 2165.415 115.5484) 
(list 2165.415 115.3714) 
(list 2239.4375 114.8214)))
(apply 'command (append '("pline") coords '("c")))
(setq currobj (ssadd (entlast) currobj))
(setq coords (list 
(list 2239.4375 114.6784) 
(list 2165.415 115.2284) 
(list 2165.415 115.0514) 
(list 2239.4375 114.6014)))
(apply 'command (append '("pline") coords '("c")))
(setq currobj (ssadd (entlast) currobj))
(setq coords (list 
(list 2239.4375 114.4584) 
(list 2165.415 114.9084) 
(list 2165.415 114.7314) 
(list 2239.4375 114.3814)))
(apply 'command (append '("pline") coords '("c")))
(setq currobj (ssadd (entlast) currobj))
(setq coords (list 
(list 2239.4375 114.2384) 
(list 2165.415 114.5884) 
(list 2165.415 114.4114) 
(list 2239.4375 114.1614)))
(apply 'command (append '("pline") coords '("c")))
(setq currobj (ssadd (entlast) currobj))
(setq coords (list 
(list 2239.4375 114.0184) 
(list 2165.415 114.2684) 
(list 2165.415 114.0914) 
(list 2239.4375 113.9414)))
(apply 'command (append '("pline") coords '("c")))
(setq currobj (ssadd (entlast) currobj))
(setq coords (list 
(list 2239.4375 113.7984) 
(list 2165.415 113.9484) 
(list 2165.415 113.7714) 
(list 2239.4375 113.7214)))
(apply 'command (append '("pline") coords '("c")))
(setq currobj (ssadd (entlast) currobj))
(setq coords (list 
(list 2239.4375 113.5784) 
(list 2165.415 113.6284) 
(list 2165.415 113.4514) 
(list 2239.4375 113.5014)))
(apply 'command (append '("pline") coords '("c")))
(setq currobj (ssadd (entlast) currobj))
(setq coords (list 
(list 2239.4375 113.3584) 
(list 2165.415 113.3084) 
(list 2165.415 113.1314) 
(list 2239.4375 113.2814)))
(apply 'command (append '("pline") coords '("c")))
(setq currobj (ssadd (entlast) currobj))
(setq coords (list 
(list 2239.4375 113.1384) 
(list 2165.415 112.9884) 
(list 2165.415 112.8114) 
(list 2239.4375 113.0614)))
(apply 'command (append '("pline") coords '("c")))
(setq currobj (ssadd (entlast) currobj))
(setq coords (list 
(list 2239.4375 112.9184) 
(list 2165.415 112.6684) 
(list 2165.415 112.4914) 
(list 2239.4375 112.8414)))
(apply 'command (append '("pline") coords '("c")))
(setq currobj (ssadd (entlast) currobj))
(setq coords (list 
(list 2239.4375 112.6984) 
(list 2165.415 112.3484) 
(list 2165.415 112.1714) 
(list 2239.4375 112.6214)))
(apply 'command (append '("pline") coords '("c")))
(setq currobj (ssadd (entlast) currobj))
(setq coords (list 
(list 2239.4375 112.4784) 
(list 2165.415 112.0284) 
(list 2165.415 111.8514) 
(list 2239.4375 112.4014)))
(apply 'command (append '("pline") coords '("c")))
(setq currobj (ssadd (entlast) currobj))
(setq coords (list 
(list 2239.4375 112.2584) 
(list 2165.415 111.7084) 
(list 2165.415 111.5314) 
(list 2239.4375 112.1814)))
(apply 'command (append '("pline") coords '("c")))
(setq currobj (ssadd (entlast) currobj))
(setq coords (list 
(list 2239.4375 112.0384) 
(list 2165.415 111.3884) 
(list 2165.415 111.2114) 
(list 2239.4375 111.9614)))
(apply 'command (append '("pline") coords '("c")))
(setq currobj (ssadd (entlast) currobj))
(command "_layer" "set" "nitride" "")
(command "_layer" "set" "text" "")
(command "_circle" "2239.0625,100.8184" "0.075")
(command "_circle" "2239.0625,101.1184" "0.075")
(command "_circle" "2239.0625,101.4184" "0.075")
(command "_circle" "2239.0625,101.7184" "0.075")
(command "_circle" "2239.0625,102.0184" "0.075")
(command "_circle" "2238.7625,100.8184" "0.075")
(command "_circle" "2238.7625,101.1184" "0.075")
(command "_circle" "2238.7625,101.4184" "0.075")
(command "_circle" "2238.7625,101.7184" "0.075")
(command "_circle" "2238.7625,102.0184" "0.075")
(command "_circle" "2238.4625,100.8184" "0.075")
(command "_circle" "2238.4625,101.1184" "0.075")
(command "_circle" "2238.4625,101.4184" "0.075")
(command "_circle" "2238.4625,101.7184" "0.075")
(command "_circle" "2238.4625,102.0184" "0.075")
(command "_circle" "2238.1625,100.8184" "0.075")
(command "_circle" "2238.1625,101.1184" "0.075")
(command "_circle" "2238.1625,101.4184" "0.075")
(command "_circle" "2238.1625,101.7184" "0.075")
(command "_circle" "2238.1625,102.0184" "0.075")
(command "_circle" "2237.8625,100.8184" "0.075")
(command "_circle" "2237.8625,101.1184" "0.075")
(command "_circle" "2237.8625,101.4184" "0.075")
(command "_circle" "2237.8625,101.7184" "0.075")
(command "_circle" "2237.8625,102.0184" "0.075")
(command "_layer" "set" "nitride" "")
(setq coords (list 
(list 2240.2625 126.2614) 
(list 2240.2625 241.9061) 
(list 2239.7375 241.9061) 
(list 2239.7375 126.2614)))
(apply 'command (append '("pline") coords '("c")))
(setq currobj (ssadd (entlast) currobj))
(command "_layer" "set" "prebias" "")
(command "_rectangle" "2239.7375,126.2614" "2240.2625,241.9061")
(setq currobj (ssadd (entlast) currobj))
(command "_layer" "set" "nitride" "")
(setq coords (list 
(list 2240.2625 241.9061) 
(list 2240.5625 251.9061) 
(list 2240.5625 251.9061) 
(list 2240.5625 252.9061) 
(list 2314.585 252.1561) 
(list 2314.585 257.0991) 
(list 2240.5625 256.3491) 
(list 2240.5625 257.3491) 
(list 2240.5625 257.3491) 
(list 2240.2625 267.3491) 
(list 2239.7375 267.3491) 
(list 2239.4375 257.3491) 
(list 2239.4375 257.3491) 
(list 2239.4375 256.3491) 
(list 2165.415 257.0991) 
(list 2165.415 252.1561) 
(list 2239.4375 252.9061) 
(list 2239.4375 251.9061) 
(list 2239.4375 251.9061) 
(list 2239.7375 241.9061)))
(apply 'command (append '("pline") coords '("c")))
(setq currobj (ssadd (entlast) currobj))
(command "_layer" "set" "prebias" "")
(setq coords (list 
(list 2239.4375 241.9061) 
(list 2239.4375 252.9061) 
(list 2165.415 252.1561) 
(list 2165.415 257.0991) 
(list 2239.4375 256.3491) 
(list 2239.4375 267.3491) 
(list 2240.5625 267.3491) 
(list 2240.5625 256.3491) 
(list 2314.585 257.0991) 
(list 2314.585 252.1561) 
(list 2240.5625 252.9061) 
(list 2240.5625 241.9061)))
(apply 'command (append '("pline") coords '("c")))
(setq currobj (ssadd (entlast) currobj))
(command "_layer" "set" "nitride" "")
(command "_layer" "set" "fda1" "")
(setq coords (list 
(list 2240.5625 253.0491) 
(list 2314.585 252.2991) 
(list 2314.585 252.4761) 
(list 2240.5625 253.1261)))
(apply 'command (append '("pline") coords '("c")))
(setq currobj (ssadd (entlast) currobj))
(setq coords (list 
(list 2240.5625 253.2691) 
(list 2314.585 252.6191) 
(list 2314.585 252.7961) 
(list 2240.5625 253.3461)))
(apply 'command (append '("pline") coords '("c")))
(setq currobj (ssadd (entlast) currobj))
(setq coords (list 
(list 2240.5625 253.4891) 
(list 2314.585 252.9391) 
(list 2314.585 253.1161) 
(list 2240.5625 253.5661)))
(apply 'command (append '("pline") coords '("c")))
(setq currobj (ssadd (entlast) currobj))
(setq coords (list 
(list 2240.5625 253.7091) 
(list 2314.585 253.2591) 
(list 2314.585 253.4361) 
(list 2240.5625 253.7861)))
(apply 'command (append '("pline") coords '("c")))
(setq currobj (ssadd (entlast) currobj))
(setq coords (list 
(list 2240.5625 253.9291) 
(list 2314.585 253.5791) 
(list 2314.585 253.7561) 
(list 2240.5625 254.0061)))
(apply 'command (append '("pline") coords '("c")))
(setq currobj (ssadd (entlast) currobj))
(setq coords (list 
(list 2240.5625 254.1491) 
(list 2314.585 253.8991) 
(list 2314.585 254.0761) 
(list 2240.5625 254.2261)))
(apply 'command (append '("pline") coords '("c")))
(setq currobj (ssadd (entlast) currobj))
(setq coords (list 
(list 2240.5625 254.3691) 
(list 2314.585 254.2191) 
(list 2314.585 254.3961) 
(list 2240.5625 254.4461)))
(apply 'command (append '("pline") coords '("c")))
(setq currobj (ssadd (entlast) currobj))
(setq coords (list 
(list 2240.5625 254.5891) 
(list 2314.585 254.5391) 
(list 2314.585 254.7161) 
(list 2240.5625 254.6661)))
(apply 'command (append '("pline") coords '("c")))
(setq currobj (ssadd (entlast) currobj))
(setq coords (list 
(list 2240.5625 254.8091) 
(list 2314.585 254.8591) 
(list 2314.585 255.0361) 
(list 2240.5625 254.8861)))
(apply 'command (append '("pline") coords '("c")))
(setq currobj (ssadd (entlast) currobj))
(setq coords (list 
(list 2240.5625 255.0291) 
(list 2314.585 255.1791) 
(list 2314.585 255.3561) 
(list 2240.5625 255.1061)))
(apply 'command (append '("pline") coords '("c")))
(setq currobj (ssadd (entlast) currobj))
(setq coords (list 
(list 2240.5625 255.2491) 
(list 2314.585 255.4991) 
(list 2314.585 255.6761) 
(list 2240.5625 255.3261)))
(apply 'command (append '("pline") coords '("c")))
(setq currobj (ssadd (entlast) currobj))
(setq coords (list 
(list 2240.5625 255.4691) 
(list 2314.585 255.8191) 
(list 2314.585 255.9961) 
(list 2240.5625 255.5461)))
(apply 'command (append '("pline") coords '("c")))
(setq currobj (ssadd (entlast) currobj))
(setq coords (list 
(list 2240.5625 255.6891) 
(list 2314.585 256.1391) 
(list 2314.585 256.3161) 
(list 2240.5625 255.7661)))
(apply 'command (append '("pline") coords '("c")))
(setq currobj (ssadd (entlast) currobj))
(setq coords (list 
(list 2240.5625 255.9091) 
(list 2314.585 256.4591) 
(list 2314.585 256.6361) 
(list 2240.5625 255.9861)))
(apply 'command (append '("pline") coords '("c")))
(setq currobj (ssadd (entlast) currobj))
(setq coords (list 
(list 2240.5625 256.1291) 
(list 2314.585 256.7791) 
(list 2314.585 256.9561) 
(list 2240.5625 256.2061)))
(apply 'command (append '("pline") coords '("c")))
(setq currobj (ssadd (entlast) currobj))
(setq coords (list 
(list 2239.4375 256.2061) 
(list 2165.415 256.9561) 
(list 2165.415 256.7791) 
(list 2239.4375 256.1291)))
(apply 'command (append '("pline") coords '("c")))
(setq currobj (ssadd (entlast) currobj))
(setq coords (list 
(list 2239.4375 255.9861) 
(list 2165.415 256.6361) 
(list 2165.415 256.4591) 
(list 2239.4375 255.9091)))
(apply 'command (append '("pline") coords '("c")))
(setq currobj (ssadd (entlast) currobj))
(setq coords (list 
(list 2239.4375 255.7661) 
(list 2165.415 256.3161) 
(list 2165.415 256.1391) 
(list 2239.4375 255.6891)))
(apply 'command (append '("pline") coords '("c")))
(setq currobj (ssadd (entlast) currobj))
(setq coords (list 
(list 2239.4375 255.5461) 
(list 2165.415 255.9961) 
(list 2165.415 255.8191) 
(list 2239.4375 255.4691)))
(apply 'command (append '("pline") coords '("c")))
(setq currobj (ssadd (entlast) currobj))
(setq coords (list 
(list 2239.4375 255.3261) 
(list 2165.415 255.6761) 
(list 2165.415 255.4991) 
(list 2239.4375 255.2491)))
(apply 'command (append '("pline") coords '("c")))
(setq currobj (ssadd (entlast) currobj))
(setq coords (list 
(list 2239.4375 255.1061) 
(list 2165.415 255.3561) 
(list 2165.415 255.1791) 
(list 2239.4375 255.0291)))
(apply 'command (append '("pline") coords '("c")))
(setq currobj (ssadd (entlast) currobj))
(setq coords (list 
(list 2239.4375 254.8861) 
(list 2165.415 255.0361) 
(list 2165.415 254.8591) 
(list 2239.4375 254.8091)))
(apply 'command (append '("pline") coords '("c")))
(setq currobj (ssadd (entlast) currobj))
(setq coords (list 
(list 2239.4375 254.6661) 
(list 2165.415 254.7161) 
(list 2165.415 254.5391) 
(list 2239.4375 254.5891)))
(apply 'command (append '("pline") coords '("c")))
(setq currobj (ssadd (entlast) currobj))
(setq coords (list 
(list 2239.4375 254.4461) 
(list 2165.415 254.3961) 
(list 2165.415 254.2191) 
(list 2239.4375 254.3691)))
(apply 'command (append '("pline") coords '("c")))
(setq currobj (ssadd (entlast) currobj))
(setq coords (list 
(list 2239.4375 254.2261) 
(list 2165.415 254.0761) 
(list 2165.415 253.8991) 
(list 2239.4375 254.1491)))
(apply 'command (append '("pline") coords '("c")))
(setq currobj (ssadd (entlast) currobj))
(setq coords (list 
(list 2239.4375 254.0061) 
(list 2165.415 253.7561) 
(list 2165.415 253.5791) 
(list 2239.4375 253.9291)))
(apply 'command (append '("pline") coords '("c")))
(setq currobj (ssadd (entlast) currobj))
(setq coords (list 
(list 2239.4375 253.7861) 
(list 2165.415 253.4361) 
(list 2165.415 253.2591) 
(list 2239.4375 253.7091)))
(apply 'command (append '("pline") coords '("c")))
(setq currobj (ssadd (entlast) currobj))
(setq coords (list 
(list 2239.4375 253.5661) 
(list 2165.415 253.1161) 
(list 2165.415 252.9391) 
(list 2239.4375 253.4891)))
(apply 'command (append '("pline") coords '("c")))
(setq currobj (ssadd (entlast) currobj))
(setq coords (list 
(list 2239.4375 253.3461) 
(list 2165.415 252.7961) 
(list 2165.415 252.6191) 
(list 2239.4375 253.2691)))
(apply 'command (append '("pline") coords '("c")))
(setq currobj (ssadd (entlast) currobj))
(setq coords (list 
(list 2239.4375 253.1261) 
(list 2165.415 252.4761) 
(list 2165.415 252.2991) 
(list 2239.4375 253.0491)))
(apply 'command (append '("pline") coords '("c")))
(setq currobj (ssadd (entlast) currobj))
(command "_layer" "set" "nitride" "")
(command "_layer" "set" "text" "")
(command "_circle" "2239.0625,241.9061" "0.075")
(command "_circle" "2239.0625,242.2061" "0.075")
(command "_circle" "2239.0625,242.5061" "0.075")
(command "_circle" "2239.0625,242.8061" "0.075")
(command "_circle" "2239.0625,243.1061" "0.075")
(command "_circle" "2238.7625,241.9061" "0.075")
(command "_circle" "2238.7625,242.2061" "0.075")
(command "_circle" "2238.7625,242.5061" "0.075")
(command "_circle" "2238.7625,242.8061" "0.075")
(command "_circle" "2238.7625,243.1061" "0.075")
(command "_circle" "2238.4625,241.9061" "0.075")
(command "_circle" "2238.4625,242.2061" "0.075")
(command "_circle" "2238.4625,242.5061" "0.075")
(command "_circle" "2238.4625,242.8061" "0.075")
(command "_circle" "2238.4625,243.1061" "0.075")
(command "_circle" "2238.1625,241.9061" "0.075")
(command "_circle" "2238.1625,242.2061" "0.075")
(command "_circle" "2238.1625,242.5061" "0.075")
(command "_circle" "2238.1625,242.8061" "0.075")
(command "_circle" "2238.1625,243.1061" "0.075")
(command "_circle" "2237.8625,241.9061" "0.075")
(command "_circle" "2237.8625,242.2061" "0.075")
(command "_circle" "2237.8625,242.5061" "0.075")
(command "_circle" "2237.8625,242.8061" "0.075")
(command "_circle" "2237.8625,243.1061" "0.075")
(command "_layer" "set" "nitride" "")
(setq coords (list 
(list 2240.2625 267.3491) 
(list 2240.2625 382.9939) 
(list 2239.7375 382.9939) 
(list 2239.7375 267.3491)))
(apply 'command (append '("pline") coords '("c")))
(setq currobj (ssadd (entlast) currobj))
(command "_layer" "set" "prebias" "")
(command "_rectangle" "2239.7375,267.3491" "2240.2625,382.9939")
(setq currobj (ssadd (entlast) currobj))
(command "_layer" "set" "nitride" "")
(setq coords (list 
(list 2240.2625 382.9939) 
(list 2240.5625 392.9939) 
(list 2240.5625 392.9939) 
(list 2240.5625 393.9939) 
(list 2314.585 393.2439) 
(list 2314.585 398.1869) 
(list 2240.5625 397.4369) 
(list 2240.5625 398.4369) 
(list 2240.5625 398.4369) 
(list 2240.2625 408.4369) 
(list 2239.7375 408.4369) 
(list 2239.4375 398.4369) 
(list 2239.4375 398.4369) 
(list 2239.4375 397.4369) 
(list 2165.415 398.1869) 
(list 2165.415 393.2439) 
(list 2239.4375 393.9939) 
(list 2239.4375 392.9939) 
(list 2239.4375 392.9939) 
(list 2239.7375 382.9939)))
(apply 'command (append '("pline") coords '("c")))
(setq currobj (ssadd (entlast) currobj))
(command "_layer" "set" "prebias" "")
(setq coords (list 
(list 2239.4375 382.9939) 
(list 2239.4375 393.9939) 
(list 2165.415 393.2439) 
(list 2165.415 398.1869) 
(list 2239.4375 397.4369) 
(list 2239.4375 408.4369) 
(list 2240.5625 408.4369) 
(list 2240.5625 397.4369) 
(list 2314.585 398.1869) 
(list 2314.585 393.2439) 
(list 2240.5625 393.9939) 
(list 2240.5625 382.9939)))
(apply 'command (append '("pline") coords '("c")))
(setq currobj (ssadd (entlast) currobj))
(command "_layer" "set" "nitride" "")
(command "_layer" "set" "fda1" "")
(setq coords (list 
(list 2240.5625 394.1369) 
(list 2314.585 393.3869) 
(list 2314.585 393.5639) 
(list 2240.5625 394.2139)))
(apply 'command (append '("pline") coords '("c")))
(setq currobj (ssadd (entlast) currobj))
(setq coords (list 
(list 2240.5625 394.3569) 
(list 2314.585 393.7069) 
(list 2314.585 393.8839) 
(list 2240.5625 394.4339)))
(apply 'command (append '("pline") coords '("c")))
(setq currobj (ssadd (entlast) currobj))
(setq coords (list 
(list 2240.5625 394.5769) 
(list 2314.585 394.0269) 
(list 2314.585 394.2039) 
(list 2240.5625 394.6539)))
(apply 'command (append '("pline") coords '("c")))
(setq currobj (ssadd (entlast) currobj))
(setq coords (list 
(list 2240.5625 394.7969) 
(list 2314.585 394.3469) 
(list 2314.585 394.5239) 
(list 2240.5625 394.8739)))
(apply 'command (append '("pline") coords '("c")))
(setq currobj (ssadd (entlast) currobj))
(setq coords (list 
(list 2240.5625 395.0169) 
(list 2314.585 394.6669) 
(list 2314.585 394.8439) 
(list 2240.5625 395.0939)))
(apply 'command (append '("pline") coords '("c")))
(setq currobj (ssadd (entlast) currobj))
(setq coords (list 
(list 2240.5625 395.2369) 
(list 2314.585 394.9869) 
(list 2314.585 395.1639) 
(list 2240.5625 395.3139)))
(apply 'command (append '("pline") coords '("c")))
(setq currobj (ssadd (entlast) currobj))
(setq coords (list 
(list 2240.5625 395.4569) 
(list 2314.585 395.3069) 
(list 2314.585 395.4839) 
(list 2240.5625 395.5339)))
(apply 'command (append '("pline") coords '("c")))
(setq currobj (ssadd (entlast) currobj))
(setq coords (list 
(list 2240.5625 395.6769) 
(list 2314.585 395.6269) 
(list 2314.585 395.8039) 
(list 2240.5625 395.7539)))
(apply 'command (append '("pline") coords '("c")))
(setq currobj (ssadd (entlast) currobj))
(setq coords (list 
(list 2240.5625 395.8969) 
(list 2314.585 395.9469) 
(list 2314.585 396.1239) 
(list 2240.5625 395.9739)))
(apply 'command (append '("pline") coords '("c")))
(setq currobj (ssadd (entlast) currobj))
(setq coords (list 
(list 2240.5625 396.1169) 
(list 2314.585 396.2669) 
(list 2314.585 396.4439) 
(list 2240.5625 396.1939)))
(apply 'command (append '("pline") coords '("c")))
(setq currobj (ssadd (entlast) currobj))
(setq coords (list 
(list 2240.5625 396.3369) 
(list 2314.585 396.5869) 
(list 2314.585 396.7639) 
(list 2240.5625 396.4139)))
(apply 'command (append '("pline") coords '("c")))
(setq currobj (ssadd (entlast) currobj))
(setq coords (list 
(list 2240.5625 396.5569) 
(list 2314.585 396.9069) 
(list 2314.585 397.0839) 
(list 2240.5625 396.6339)))
(apply 'command (append '("pline") coords '("c")))
(setq currobj (ssadd (entlast) currobj))
(setq coords (list 
(list 2240.5625 396.7769) 
(list 2314.585 397.2269) 
(list 2314.585 397.4039) 
(list 2240.5625 396.8539)))
(apply 'command (append '("pline") coords '("c")))
(setq currobj (ssadd (entlast) currobj))
(setq coords (list 
(list 2240.5625 396.9969) 
(list 2314.585 397.5469) 
(list 2314.585 397.7239) 
(list 2240.5625 397.0739)))
(apply 'command (append '("pline") coords '("c")))
(setq currobj (ssadd (entlast) currobj))
(setq coords (list 
(list 2240.5625 397.2169) 
(list 2314.585 397.8669) 
(list 2314.585 398.0439) 
(list 2240.5625 397.2939)))
(apply 'command (append '("pline") coords '("c")))
(setq currobj (ssadd (entlast) currobj))
(setq coords (list 
(list 2239.4375 397.2939) 
(list 2165.415 398.0439) 
(list 2165.415 397.8669) 
(list 2239.4375 397.2169)))
(apply 'command (append '("pline") coords '("c")))
(setq currobj (ssadd (entlast) currobj))
(setq coords (list 
(list 2239.4375 397.0739) 
(list 2165.415 397.7239) 
(list 2165.415 397.5469) 
(list 2239.4375 396.9969)))
(apply 'command (append '("pline") coords '("c")))
(setq currobj (ssadd (entlast) currobj))
(setq coords (list 
(list 2239.4375 396.8539) 
(list 2165.415 397.4039) 
(list 2165.415 397.2269) 
(list 2239.4375 396.7769)))
(apply 'command (append '("pline") coords '("c")))
(setq currobj (ssadd (entlast) currobj))
(setq coords (list 
(list 2239.4375 396.6339) 
(list 2165.415 397.0839) 
(list 2165.415 396.9069) 
(list 2239.4375 396.5569)))
(apply 'command (append '("pline") coords '("c")))
(setq currobj (ssadd (entlast) currobj))
(setq coords (list 
(list 2239.4375 396.4139) 
(list 2165.415 396.7639) 
(list 2165.415 396.5869) 
(list 2239.4375 396.3369)))
(apply 'command (append '("pline") coords '("c")))
(setq currobj (ssadd (entlast) currobj))
(setq coords (list 
(list 2239.4375 396.1939) 
(list 2165.415 396.4439) 
(list 2165.415 396.2669) 
(list 2239.4375 396.1169)))
(apply 'command (append '("pline") coords '("c")))
(setq currobj (ssadd (entlast) currobj))
(setq coords (list 
(list 2239.4375 395.9739) 
(list 2165.415 396.1239) 
(list 2165.415 395.9469) 
(list 2239.4375 395.8969)))
(apply 'command (append '("pline") coords '("c")))
(setq currobj (ssadd (entlast) currobj))
(setq coords (list 
(list 2239.4375 395.7539) 
(list 2165.415 395.8039) 
(list 2165.415 395.6269) 
(list 2239.4375 395.6769)))
(apply 'command (append '("pline") coords '("c")))
(setq currobj (ssadd (entlast) currobj))
(setq coords (list 
(list 2239.4375 395.5339) 
(list 2165.415 395.4839) 
(list 2165.415 395.3069) 
(list 2239.4375 395.4569)))
(apply 'command (append '("pline") coords '("c")))
(setq currobj (ssadd (entlast) currobj))
(setq coords (list 
(list 2239.4375 395.3139) 
(list 2165.415 395.1639) 
(list 2165.415 394.9869) 
(list 2239.4375 395.2369)))
(apply 'command (append '("pline") coords '("c")))
(setq currobj (ssadd (entlast) currobj))
(setq coords (list 
(list 2239.4375 395.0939) 
(list 2165.415 394.8439) 
(list 2165.415 394.6669) 
(list 2239.4375 395.0169)))
(apply 'command (append '("pline") coords '("c")))
(setq currobj (ssadd (entlast) currobj))
(setq coords (list 
(list 2239.4375 394.8739) 
(list 2165.415 394.5239) 
(list 2165.415 394.3469) 
(list 2239.4375 394.7969)))
(apply 'command (append '("pline") coords '("c")))
(setq currobj (ssadd (entlast) currobj))
(setq coords (list 
(list 2239.4375 394.6539) 
(list 2165.415 394.2039) 
(list 2165.415 394.0269) 
(list 2239.4375 394.5769)))
(apply 'command (append '("pline") coords '("c")))
(setq currobj (ssadd (entlast) currobj))
(setq coords (list 
(list 2239.4375 394.4339) 
(list 2165.415 393.8839) 
(list 2165.415 393.7069) 
(list 2239.4375 394.3569)))
(apply 'command (append '("pline") coords '("c")))
(setq currobj (ssadd (entlast) currobj))
(setq coords (list 
(list 2239.4375 394.2139) 
(list 2165.415 393.5639) 
(list 2165.415 393.3869) 
(list 2239.4375 394.1369)))
(apply 'command (append '("pline") coords '("c")))
(setq currobj (ssadd (entlast) currobj))
(command "_layer" "set" "nitride" "")
(command "_layer" "set" "text" "")
(command "_circle" "2239.0625,382.9939" "0.075")
(command "_circle" "2239.0625,383.2939" "0.075")
(command "_circle" "2239.0625,383.5939" "0.075")
(command "_circle" "2239.0625,383.8939" "0.075")
(command "_circle" "2239.0625,384.1939" "0.075")
(command "_circle" "2238.7625,382.9939" "0.075")
(command "_circle" "2238.7625,383.2939" "0.075")
(command "_circle" "2238.7625,383.5939" "0.075")
(command "_circle" "2238.7625,383.8939" "0.075")
(command "_circle" "2238.7625,384.1939" "0.075")
(command "_circle" "2238.4625,382.9939" "0.075")
(command "_circle" "2238.4625,383.2939" "0.075")
(command "_circle" "2238.4625,383.5939" "0.075")
(command "_circle" "2238.4625,383.8939" "0.075")
(command "_circle" "2238.4625,384.1939" "0.075")
(command "_circle" "2238.1625,382.9939" "0.075")
(command "_circle" "2238.1625,383.2939" "0.075")
(command "_circle" "2238.1625,383.5939" "0.075")
(command "_circle" "2238.1625,383.8939" "0.075")
(command "_circle" "2238.1625,384.1939" "0.075")
(command "_circle" "2237.8625,382.9939" "0.075")
(command "_circle" "2237.8625,383.2939" "0.075")
(command "_circle" "2237.8625,383.5939" "0.075")
(command "_circle" "2237.8625,383.8939" "0.075")
(command "_circle" "2237.8625,384.1939" "0.075")
(command "_layer" "set" "nitride" "")
(setq coords (list 
(list 2240.2625 408.4369) 
(list 2240.2625 524.0816) 
(list 2239.7375 524.0816) 
(list 2239.7375 408.4369)))
(apply 'command (append '("pline") coords '("c")))
(setq currobj (ssadd (entlast) currobj))
(command "_layer" "set" "prebias" "")
(command "_rectangle" "2239.7375,408.4369" "2240.2625,524.0816")
(setq currobj (ssadd (entlast) currobj))
(command "_layer" "set" "nitride" "")
(setq coords (list 
(list 2240.2625 524.0816) 
(list 2240.5625 534.0816) 
(list 2240.5625 534.0816) 
(list 2240.5625 535.0816) 
(list 2314.585 534.3316) 
(list 2314.585 539.2746) 
(list 2240.5625 538.5246) 
(list 2240.5625 539.5246) 
(list 2240.5625 539.5246) 
(list 2240.2625 549.5246) 
(list 2239.7375 549.5246) 
(list 2239.4375 539.5246) 
(list 2239.4375 539.5246) 
(list 2239.4375 538.5246) 
(list 2165.415 539.2746) 
(list 2165.415 534.3316) 
(list 2239.4375 535.0816) 
(list 2239.4375 534.0816) 
(list 2239.4375 534.0816) 
(list 2239.7375 524.0816)))
(apply 'command (append '("pline") coords '("c")))
(setq currobj (ssadd (entlast) currobj))
(command "_layer" "set" "prebias" "")
(setq coords (list 
(list 2239.4375 524.0816) 
(list 2239.4375 535.0816) 
(list 2165.415 534.3316) 
(list 2165.415 539.2746) 
(list 2239.4375 538.5246) 
(list 2239.4375 549.5246) 
(list 2240.5625 549.5246) 
(list 2240.5625 538.5246) 
(list 2314.585 539.2746) 
(list 2314.585 534.3316) 
(list 2240.5625 535.0816) 
(list 2240.5625 524.0816)))
(apply 'command (append '("pline") coords '("c")))
(setq currobj (ssadd (entlast) currobj))
(command "_layer" "set" "nitride" "")
(command "_layer" "set" "fda1" "")
(setq coords (list 
(list 2240.5625 535.2246) 
(list 2314.585 534.4746) 
(list 2314.585 534.6516) 
(list 2240.5625 535.3016)))
(apply 'command (append '("pline") coords '("c")))
(setq currobj (ssadd (entlast) currobj))
(setq coords (list 
(list 2240.5625 535.4446) 
(list 2314.585 534.7946) 
(list 2314.585 534.9716) 
(list 2240.5625 535.5216)))
(apply 'command (append '("pline") coords '("c")))
(setq currobj (ssadd (entlast) currobj))
(setq coords (list 
(list 2240.5625 535.6646) 
(list 2314.585 535.1146) 
(list 2314.585 535.2916) 
(list 2240.5625 535.7416)))
(apply 'command (append '("pline") coords '("c")))
(setq currobj (ssadd (entlast) currobj))
(setq coords (list 
(list 2240.5625 535.8846) 
(list 2314.585 535.4346) 
(list 2314.585 535.6116) 
(list 2240.5625 535.9616)))
(apply 'command (append '("pline") coords '("c")))
(setq currobj (ssadd (entlast) currobj))
(setq coords (list 
(list 2240.5625 536.1046) 
(list 2314.585 535.7546) 
(list 2314.585 535.9316) 
(list 2240.5625 536.1816)))
(apply 'command (append '("pline") coords '("c")))
(setq currobj (ssadd (entlast) currobj))
(setq coords (list 
(list 2240.5625 536.3246) 
(list 2314.585 536.0746) 
(list 2314.585 536.2516) 
(list 2240.5625 536.4016)))
(apply 'command (append '("pline") coords '("c")))
(setq currobj (ssadd (entlast) currobj))
(setq coords (list 
(list 2240.5625 536.5446) 
(list 2314.585 536.3946) 
(list 2314.585 536.5716) 
(list 2240.5625 536.6216)))
(apply 'command (append '("pline") coords '("c")))
(setq currobj (ssadd (entlast) currobj))
(setq coords (list 
(list 2240.5625 536.7646) 
(list 2314.585 536.7146) 
(list 2314.585 536.8916) 
(list 2240.5625 536.8416)))
(apply 'command (append '("pline") coords '("c")))
(setq currobj (ssadd (entlast) currobj))
(setq coords (list 
(list 2240.5625 536.9846) 
(list 2314.585 537.0346) 
(list 2314.585 537.2116) 
(list 2240.5625 537.0616)))
(apply 'command (append '("pline") coords '("c")))
(setq currobj (ssadd (entlast) currobj))
(setq coords (list 
(list 2240.5625 537.2046) 
(list 2314.585 537.3546) 
(list 2314.585 537.5316) 
(list 2240.5625 537.2816)))
(apply 'command (append '("pline") coords '("c")))
(setq currobj (ssadd (entlast) currobj))
(setq coords (list 
(list 2240.5625 537.4246) 
(list 2314.585 537.6746) 
(list 2314.585 537.8516) 
(list 2240.5625 537.5016)))
(apply 'command (append '("pline") coords '("c")))
(setq currobj (ssadd (entlast) currobj))
(setq coords (list 
(list 2240.5625 537.6446) 
(list 2314.585 537.9946) 
(list 2314.585 538.1716) 
(list 2240.5625 537.7216)))
(apply 'command (append '("pline") coords '("c")))
(setq currobj (ssadd (entlast) currobj))
(setq coords (list 
(list 2240.5625 537.8646) 
(list 2314.585 538.3146) 
(list 2314.585 538.4916) 
(list 2240.5625 537.9416)))
(apply 'command (append '("pline") coords '("c")))
(setq currobj (ssadd (entlast) currobj))
(setq coords (list 
(list 2240.5625 538.0846) 
(list 2314.585 538.6346) 
(list 2314.585 538.8116) 
(list 2240.5625 538.1616)))
(apply 'command (append '("pline") coords '("c")))
(setq currobj (ssadd (entlast) currobj))
(setq coords (list 
(list 2240.5625 538.3046) 
(list 2314.585 538.9546) 
(list 2314.585 539.1316) 
(list 2240.5625 538.3816)))
(apply 'command (append '("pline") coords '("c")))
(setq currobj (ssadd (entlast) currobj))
(setq coords (list 
(list 2239.4375 538.3816) 
(list 2165.415 539.1316) 
(list 2165.415 538.9546) 
(list 2239.4375 538.3046)))
(apply 'command (append '("pline") coords '("c")))
(setq currobj (ssadd (entlast) currobj))
(setq coords (list 
(list 2239.4375 538.1616) 
(list 2165.415 538.8116) 
(list 2165.415 538.6346) 
(list 2239.4375 538.0846)))
(apply 'command (append '("pline") coords '("c")))
(setq currobj (ssadd (entlast) currobj))
(setq coords (list 
(list 2239.4375 537.9416) 
(list 2165.415 538.4916) 
(list 2165.415 538.3146) 
(list 2239.4375 537.8646)))
(apply 'command (append '("pline") coords '("c")))
(setq currobj (ssadd (entlast) currobj))
(setq coords (list 
(list 2239.4375 537.7216) 
(list 2165.415 538.1716) 
(list 2165.415 537.9946) 
(list 2239.4375 537.6446)))
(apply 'command (append '("pline") coords '("c")))
(setq currobj (ssadd (entlast) currobj))
(setq coords (list 
(list 2239.4375 537.5016) 
(list 2165.415 537.8516) 
(list 2165.415 537.6746) 
(list 2239.4375 537.4246)))
(apply 'command (append '("pline") coords '("c")))
(setq currobj (ssadd (entlast) currobj))
(setq coords (list 
(list 2239.4375 537.2816) 
(list 2165.415 537.5316) 
(list 2165.415 537.3546) 
(list 2239.4375 537.2046)))
(apply 'command (append '("pline") coords '("c")))
(setq currobj (ssadd (entlast) currobj))
(setq coords (list 
(list 2239.4375 537.0616) 
(list 2165.415 537.2116) 
(list 2165.415 537.0346) 
(list 2239.4375 536.9846)))
(apply 'command (append '("pline") coords '("c")))
(setq currobj (ssadd (entlast) currobj))
(setq coords (list 
(list 2239.4375 536.8416) 
(list 2165.415 536.8916) 
(list 2165.415 536.7146) 
(list 2239.4375 536.7646)))
(apply 'command (append '("pline") coords '("c")))
(setq currobj (ssadd (entlast) currobj))
(setq coords (list 
(list 2239.4375 536.6216) 
(list 2165.415 536.5716) 
(list 2165.415 536.3946) 
(list 2239.4375 536.5446)))
(apply 'command (append '("pline") coords '("c")))
(setq currobj (ssadd (entlast) currobj))
(setq coords (list 
(list 2239.4375 536.4016) 
(list 2165.415 536.2516) 
(list 2165.415 536.0746) 
(list 2239.4375 536.3246)))
(apply 'command (append '("pline") coords '("c")))
(setq currobj (ssadd (entlast) currobj))
(setq coords (list 
(list 2239.4375 536.1816) 
(list 2165.415 535.9316) 
(list 2165.415 535.7546) 
(list 2239.4375 536.1046)))
(apply 'command (append '("pline") coords '("c")))
(setq currobj (ssadd (entlast) currobj))
(setq coords (list 
(list 2239.4375 535.9616) 
(list 2165.415 535.6116) 
(list 2165.415 535.4346) 
(list 2239.4375 535.8846)))
(apply 'command (append '("pline") coords '("c")))
(setq currobj (ssadd (entlast) currobj))
(setq coords (list 
(list 2239.4375 535.7416) 
(list 2165.415 535.2916) 
(list 2165.415 535.1146) 
(list 2239.4375 535.6646)))
(apply 'command (append '("pline") coords '("c")))
(setq currobj (ssadd (entlast) currobj))
(setq coords (list 
(list 2239.4375 535.5216) 
(list 2165.415 534.9716) 
(list 2165.415 534.7946) 
(list 2239.4375 535.4446)))
(apply 'command (append '("pline") coords '("c")))
(setq currobj (ssadd (entlast) currobj))
(setq coords (list 
(list 2239.4375 535.3016) 
(list 2165.415 534.6516) 
(list 2165.415 534.4746) 
(list 2239.4375 535.2246)))
(apply 'command (append '("pline") coords '("c")))
(setq currobj (ssadd (entlast) currobj))
(command "_layer" "set" "nitride" "")
(command "_layer" "set" "text" "")
(command "_circle" "2239.0625,524.0816" "0.075")
(command "_circle" "2239.0625,524.3816" "0.075")
(command "_circle" "2239.0625,524.6816" "0.075")
(command "_circle" "2239.0625,524.9816" "0.075")
(command "_circle" "2239.0625,525.2816" "0.075")
(command "_circle" "2238.7625,524.0816" "0.075")
(command "_circle" "2238.7625,524.3816" "0.075")
(command "_circle" "2238.7625,524.6816" "0.075")
(command "_circle" "2238.7625,524.9816" "0.075")
(command "_circle" "2238.7625,525.2816" "0.075")
(command "_circle" "2238.4625,524.0816" "0.075")
(command "_circle" "2238.4625,524.3816" "0.075")
(command "_circle" "2238.4625,524.6816" "0.075")
(command "_circle" "2238.4625,524.9816" "0.075")
(command "_circle" "2238.4625,525.2816" "0.075")
(command "_circle" "2238.1625,524.0816" "0.075")
(command "_circle" "2238.1625,524.3816" "0.075")
(command "_circle" "2238.1625,524.6816" "0.075")
(command "_circle" "2238.1625,524.9816" "0.075")
(command "_circle" "2238.1625,525.2816" "0.075")
(command "_circle" "2237.8625,524.0816" "0.075")
(command "_circle" "2237.8625,524.3816" "0.075")
(command "_circle" "2237.8625,524.6816" "0.075")
(command "_circle" "2237.8625,524.9816" "0.075")
(command "_circle" "2237.8625,525.2816" "0.075")
(command "_layer" "set" "nitride" "")
(setq coords (list 
(list 2240.2625 549.5246) 
(list 2240.2625 665.1693) 
(list 2239.7375 665.1693) 
(list 2239.7375 549.5246)))
(apply 'command (append '("pline") coords '("c")))
(setq currobj (ssadd (entlast) currobj))
(command "_layer" "set" "prebias" "")
(command "_rectangle" "2239.7375,549.5246" "2240.2625,665.1693")
(setq currobj (ssadd (entlast) currobj))
(command "_layer" "set" "nitride" "")
(setq coords (list 
(list 2240.2625 665.1693) 
(list 2240.5625 675.1693) 
(list 2240.5625 675.1693) 
(list 2240.5625 676.1693) 
(list 2314.585 675.4193) 
(list 2314.585 680.3623) 
(list 2240.5625 679.6123) 
(list 2240.5625 680.6123) 
(list 2240.5625 680.6123) 
(list 2240.2625 690.6123) 
(list 2239.7375 690.6123) 
(list 2239.4375 680.6123) 
(list 2239.4375 680.6123) 
(list 2239.4375 679.6123) 
(list 2165.415 680.3623) 
(list 2165.415 675.4193) 
(list 2239.4375 676.1693) 
(list 2239.4375 675.1693) 
(list 2239.4375 675.1693) 
(list 2239.7375 665.1693)))
(apply 'command (append '("pline") coords '("c")))
(setq currobj (ssadd (entlast) currobj))
(command "_layer" "set" "prebias" "")
(setq coords (list 
(list 2239.4375 665.1693) 
(list 2239.4375 676.1693) 
(list 2165.415 675.4193) 
(list 2165.415 680.3623) 
(list 2239.4375 679.6123) 
(list 2239.4375 690.6123) 
(list 2240.5625 690.6123) 
(list 2240.5625 679.6123) 
(list 2314.585 680.3623) 
(list 2314.585 675.4193) 
(list 2240.5625 676.1693) 
(list 2240.5625 665.1693)))
(apply 'command (append '("pline") coords '("c")))
(setq currobj (ssadd (entlast) currobj))
(command "_layer" "set" "nitride" "")
(command "_layer" "set" "fda1" "")
(setq coords (list 
(list 2240.5625 676.3123) 
(list 2314.585 675.5623) 
(list 2314.585 675.7393) 
(list 2240.5625 676.3893)))
(apply 'command (append '("pline") coords '("c")))
(setq currobj (ssadd (entlast) currobj))
(setq coords (list 
(list 2240.5625 676.5323) 
(list 2314.585 675.8823) 
(list 2314.585 676.0593) 
(list 2240.5625 676.6093)))
(apply 'command (append '("pline") coords '("c")))
(setq currobj (ssadd (entlast) currobj))
(setq coords (list 
(list 2240.5625 676.7523) 
(list 2314.585 676.2023) 
(list 2314.585 676.3793) 
(list 2240.5625 676.8293)))
(apply 'command (append '("pline") coords '("c")))
(setq currobj (ssadd (entlast) currobj))
(setq coords (list 
(list 2240.5625 676.9723) 
(list 2314.585 676.5223) 
(list 2314.585 676.6993) 
(list 2240.5625 677.0493)))
(apply 'command (append '("pline") coords '("c")))
(setq currobj (ssadd (entlast) currobj))
(setq coords (list 
(list 2240.5625 677.1923) 
(list 2314.585 676.8423) 
(list 2314.585 677.0193) 
(list 2240.5625 677.2693)))
(apply 'command (append '("pline") coords '("c")))
(setq currobj (ssadd (entlast) currobj))
(setq coords (list 
(list 2240.5625 677.4123) 
(list 2314.585 677.1623) 
(list 2314.585 677.3393) 
(list 2240.5625 677.4893)))
(apply 'command (append '("pline") coords '("c")))
(setq currobj (ssadd (entlast) currobj))
(setq coords (list 
(list 2240.5625 677.6323) 
(list 2314.585 677.4823) 
(list 2314.585 677.6593) 
(list 2240.5625 677.7093)))
(apply 'command (append '("pline") coords '("c")))
(setq currobj (ssadd (entlast) currobj))
(setq coords (list 
(list 2240.5625 677.8523) 
(list 2314.585 677.8023) 
(list 2314.585 677.9793) 
(list 2240.5625 677.9293)))
(apply 'command (append '("pline") coords '("c")))
(setq currobj (ssadd (entlast) currobj))
(setq coords (list 
(list 2240.5625 678.0723) 
(list 2314.585 678.1223) 
(list 2314.585 678.2993) 
(list 2240.5625 678.1493)))
(apply 'command (append '("pline") coords '("c")))
(setq currobj (ssadd (entlast) currobj))
(setq coords (list 
(list 2240.5625 678.2923) 
(list 2314.585 678.4423) 
(list 2314.585 678.6193) 
(list 2240.5625 678.3693)))
(apply 'command (append '("pline") coords '("c")))
(setq currobj (ssadd (entlast) currobj))
(setq coords (list 
(list 2240.5625 678.5123) 
(list 2314.585 678.7623) 
(list 2314.585 678.9393) 
(list 2240.5625 678.5893)))
(apply 'command (append '("pline") coords '("c")))
(setq currobj (ssadd (entlast) currobj))
(setq coords (list 
(list 2240.5625 678.7323) 
(list 2314.585 679.0823) 
(list 2314.585 679.2593) 
(list 2240.5625 678.8093)))
(apply 'command (append '("pline") coords '("c")))
(setq currobj (ssadd (entlast) currobj))
(setq coords (list 
(list 2240.5625 678.9523) 
(list 2314.585 679.4023) 
(list 2314.585 679.5793) 
(list 2240.5625 679.0293)))
(apply 'command (append '("pline") coords '("c")))
(setq currobj (ssadd (entlast) currobj))
(setq coords (list 
(list 2240.5625 679.1723) 
(list 2314.585 679.7223) 
(list 2314.585 679.8993) 
(list 2240.5625 679.2493)))
(apply 'command (append '("pline") coords '("c")))
(setq currobj (ssadd (entlast) currobj))
(setq coords (list 
(list 2240.5625 679.3923) 
(list 2314.585 680.0423) 
(list 2314.585 680.2193) 
(list 2240.5625 679.4693)))
(apply 'command (append '("pline") coords '("c")))
(setq currobj (ssadd (entlast) currobj))
(setq coords (list 
(list 2239.4375 679.4693) 
(list 2165.415 680.2193) 
(list 2165.415 680.0423) 
(list 2239.4375 679.3923)))
(apply 'command (append '("pline") coords '("c")))
(setq currobj (ssadd (entlast) currobj))
(setq coords (list 
(list 2239.4375 679.2493) 
(list 2165.415 679.8993) 
(list 2165.415 679.7223) 
(list 2239.4375 679.1723)))
(apply 'command (append '("pline") coords '("c")))
(setq currobj (ssadd (entlast) currobj))
(setq coords (list 
(list 2239.4375 679.0293) 
(list 2165.415 679.5793) 
(list 2165.415 679.4023) 
(list 2239.4375 678.9523)))
(apply 'command (append '("pline") coords '("c")))
(setq currobj (ssadd (entlast) currobj))
(setq coords (list 
(list 2239.4375 678.8093) 
(list 2165.415 679.2593) 
(list 2165.415 679.0823) 
(list 2239.4375 678.7323)))
(apply 'command (append '("pline") coords '("c")))
(setq currobj (ssadd (entlast) currobj))
(setq coords (list 
(list 2239.4375 678.5893) 
(list 2165.415 678.9393) 
(list 2165.415 678.7623) 
(list 2239.4375 678.5123)))
(apply 'command (append '("pline") coords '("c")))
(setq currobj (ssadd (entlast) currobj))
(setq coords (list 
(list 2239.4375 678.3693) 
(list 2165.415 678.6193) 
(list 2165.415 678.4423) 
(list 2239.4375 678.2923)))
(apply 'command (append '("pline") coords '("c")))
(setq currobj (ssadd (entlast) currobj))
(setq coords (list 
(list 2239.4375 678.1493) 
(list 2165.415 678.2993) 
(list 2165.415 678.1223) 
(list 2239.4375 678.0723)))
(apply 'command (append '("pline") coords '("c")))
(setq currobj (ssadd (entlast) currobj))
(setq coords (list 
(list 2239.4375 677.9293) 
(list 2165.415 677.9793) 
(list 2165.415 677.8023) 
(list 2239.4375 677.8523)))
(apply 'command (append '("pline") coords '("c")))
(setq currobj (ssadd (entlast) currobj))
(setq coords (list 
(list 2239.4375 677.7093) 
(list 2165.415 677.6593) 
(list 2165.415 677.4823) 
(list 2239.4375 677.6323)))
(apply 'command (append '("pline") coords '("c")))
(setq currobj (ssadd (entlast) currobj))
(setq coords (list 
(list 2239.4375 677.4893) 
(list 2165.415 677.3393) 
(list 2165.415 677.1623) 
(list 2239.4375 677.4123)))
(apply 'command (append '("pline") coords '("c")))
(setq currobj (ssadd (entlast) currobj))
(setq coords (list 
(list 2239.4375 677.2693) 
(list 2165.415 677.0193) 
(list 2165.415 676.8423) 
(list 2239.4375 677.1923)))
(apply 'command (append '("pline") coords '("c")))
(setq currobj (ssadd (entlast) currobj))
(setq coords (list 
(list 2239.4375 677.0493) 
(list 2165.415 676.6993) 
(list 2165.415 676.5223) 
(list 2239.4375 676.9723)))
(apply 'command (append '("pline") coords '("c")))
(setq currobj (ssadd (entlast) currobj))
(setq coords (list 
(list 2239.4375 676.8293) 
(list 2165.415 676.3793) 
(list 2165.415 676.2023) 
(list 2239.4375 676.7523)))
(apply 'command (append '("pline") coords '("c")))
(setq currobj (ssadd (entlast) currobj))
(setq coords (list 
(list 2239.4375 676.6093) 
(list 2165.415 676.0593) 
(list 2165.415 675.8823) 
(list 2239.4375 676.5323)))
(apply 'command (append '("pline") coords '("c")))
(setq currobj (ssadd (entlast) currobj))
(setq coords (list 
(list 2239.4375 676.3893) 
(list 2165.415 675.7393) 
(list 2165.415 675.5623) 
(list 2239.4375 676.3123)))
(apply 'command (append '("pline") coords '("c")))
(setq currobj (ssadd (entlast) currobj))
(command "_layer" "set" "nitride" "")
(command "_layer" "set" "text" "")
(command "_circle" "2239.0625,665.1693" "0.075")
(command "_circle" "2239.0625,665.4693" "0.075")
(command "_circle" "2239.0625,665.7693" "0.075")
(command "_circle" "2239.0625,666.0693" "0.075")
(command "_circle" "2239.0625,666.3693" "0.075")
(command "_circle" "2238.7625,665.1693" "0.075")
(command "_circle" "2238.7625,665.4693" "0.075")
(command "_circle" "2238.7625,665.7693" "0.075")
(command "_circle" "2238.7625,666.0693" "0.075")
(command "_circle" "2238.7625,666.3693" "0.075")
(command "_circle" "2238.4625,665.1693" "0.075")
(command "_circle" "2238.4625,665.4693" "0.075")
(command "_circle" "2238.4625,665.7693" "0.075")
(command "_circle" "2238.4625,666.0693" "0.075")
(command "_circle" "2238.4625,666.3693" "0.075")
(command "_circle" "2238.1625,665.1693" "0.075")
(command "_circle" "2238.1625,665.4693" "0.075")
(command "_circle" "2238.1625,665.7693" "0.075")
(command "_circle" "2238.1625,666.0693" "0.075")
(command "_circle" "2238.1625,666.3693" "0.075")
(command "_circle" "2237.8625,665.1693" "0.075")
(command "_circle" "2237.8625,665.4693" "0.075")
(command "_circle" "2237.8625,665.7693" "0.075")
(command "_circle" "2237.8625,666.0693" "0.075")
(command "_circle" "2237.8625,666.3693" "0.075")
(command "_layer" "set" "nitride" "")
(setq coords (list 
(list 2240.2625 690.6123) 
(list 2240.2625 806.257) 
(list 2239.7375 806.257) 
(list 2239.7375 690.6123)))
(apply 'command (append '("pline") coords '("c")))
(setq currobj (ssadd (entlast) currobj))
(command "_layer" "set" "prebias" "")
(command "_rectangle" "2239.7375,690.6123" "2240.2625,806.257")
(setq currobj (ssadd (entlast) currobj))
(command "_layer" "set" "nitride" "")
(setq coords (list 
(list 2240.2625 806.257) 
(list 2240.5625 816.257) 
(list 2240.5625 816.257) 
(list 2240.5625 817.257) 
(list 2314.585 816.507) 
(list 2314.585 821.45) 
(list 2240.5625 820.7) 
(list 2240.5625 821.7) 
(list 2240.5625 821.7) 
(list 2240.2625 831.7) 
(list 2239.7375 831.7) 
(list 2239.4375 821.7) 
(list 2239.4375 821.7) 
(list 2239.4375 820.7) 
(list 2165.415 821.45) 
(list 2165.415 816.507) 
(list 2239.4375 817.257) 
(list 2239.4375 816.257) 
(list 2239.4375 816.257) 
(list 2239.7375 806.257)))
(apply 'command (append '("pline") coords '("c")))
(setq currobj (ssadd (entlast) currobj))
(command "_layer" "set" "prebias" "")
(setq coords (list 
(list 2239.4375 806.257) 
(list 2239.4375 817.257) 
(list 2165.415 816.507) 
(list 2165.415 821.45) 
(list 2239.4375 820.7) 
(list 2239.4375 831.7) 
(list 2240.5625 831.7) 
(list 2240.5625 820.7) 
(list 2314.585 821.45) 
(list 2314.585 816.507) 
(list 2240.5625 817.257) 
(list 2240.5625 806.257)))
(apply 'command (append '("pline") coords '("c")))
(setq currobj (ssadd (entlast) currobj))
(command "_layer" "set" "nitride" "")
(command "_layer" "set" "fda1" "")
(setq coords (list 
(list 2240.5625 817.4) 
(list 2314.585 816.65) 
(list 2314.585 816.827) 
(list 2240.5625 817.477)))
(apply 'command (append '("pline") coords '("c")))
(setq currobj (ssadd (entlast) currobj))
(setq coords (list 
(list 2240.5625 817.62) 
(list 2314.585 816.97) 
(list 2314.585 817.147) 
(list 2240.5625 817.697)))
(apply 'command (append '("pline") coords '("c")))
(setq currobj (ssadd (entlast) currobj))
(setq coords (list 
(list 2240.5625 817.84) 
(list 2314.585 817.29) 
(list 2314.585 817.467) 
(list 2240.5625 817.917)))
(apply 'command (append '("pline") coords '("c")))
(setq currobj (ssadd (entlast) currobj))
(setq coords (list 
(list 2240.5625 818.06) 
(list 2314.585 817.61) 
(list 2314.585 817.787) 
(list 2240.5625 818.137)))
(apply 'command (append '("pline") coords '("c")))
(setq currobj (ssadd (entlast) currobj))
(setq coords (list 
(list 2240.5625 818.28) 
(list 2314.585 817.93) 
(list 2314.585 818.107) 
(list 2240.5625 818.357)))
(apply 'command (append '("pline") coords '("c")))
(setq currobj (ssadd (entlast) currobj))
(setq coords (list 
(list 2240.5625 818.5) 
(list 2314.585 818.25) 
(list 2314.585 818.427) 
(list 2240.5625 818.577)))
(apply 'command (append '("pline") coords '("c")))
(setq currobj (ssadd (entlast) currobj))
(setq coords (list 
(list 2240.5625 818.72) 
(list 2314.585 818.57) 
(list 2314.585 818.747) 
(list 2240.5625 818.797)))
(apply 'command (append '("pline") coords '("c")))
(setq currobj (ssadd (entlast) currobj))
(setq coords (list 
(list 2240.5625 818.94) 
(list 2314.585 818.89) 
(list 2314.585 819.067) 
(list 2240.5625 819.017)))
(apply 'command (append '("pline") coords '("c")))
(setq currobj (ssadd (entlast) currobj))
(setq coords (list 
(list 2240.5625 819.16) 
(list 2314.585 819.21) 
(list 2314.585 819.387) 
(list 2240.5625 819.237)))
(apply 'command (append '("pline") coords '("c")))
(setq currobj (ssadd (entlast) currobj))
(setq coords (list 
(list 2240.5625 819.38) 
(list 2314.585 819.53) 
(list 2314.585 819.707) 
(list 2240.5625 819.457)))
(apply 'command (append '("pline") coords '("c")))
(setq currobj (ssadd (entlast) currobj))
(setq coords (list 
(list 2240.5625 819.6) 
(list 2314.585 819.85) 
(list 2314.585 820.027) 
(list 2240.5625 819.677)))
(apply 'command (append '("pline") coords '("c")))
(setq currobj (ssadd (entlast) currobj))
(setq coords (list 
(list 2240.5625 819.82) 
(list 2314.585 820.17) 
(list 2314.585 820.347) 
(list 2240.5625 819.897)))
(apply 'command (append '("pline") coords '("c")))
(setq currobj (ssadd (entlast) currobj))
(setq coords (list 
(list 2240.5625 820.04) 
(list 2314.585 820.49) 
(list 2314.585 820.667) 
(list 2240.5625 820.117)))
(apply 'command (append '("pline") coords '("c")))
(setq currobj (ssadd (entlast) currobj))
(setq coords (list 
(list 2240.5625 820.26) 
(list 2314.585 820.81) 
(list 2314.585 820.987) 
(list 2240.5625 820.337)))
(apply 'command (append '("pline") coords '("c")))
(setq currobj (ssadd (entlast) currobj))
(setq coords (list 
(list 2240.5625 820.48) 
(list 2314.585 821.13) 
(list 2314.585 821.307) 
(list 2240.5625 820.557)))
(apply 'command (append '("pline") coords '("c")))
(setq currobj (ssadd (entlast) currobj))
(setq coords (list 
(list 2239.4375 820.557) 
(list 2165.415 821.307) 
(list 2165.415 821.13) 
(list 2239.4375 820.48)))
(apply 'command (append '("pline") coords '("c")))
(setq currobj (ssadd (entlast) currobj))
(setq coords (list 
(list 2239.4375 820.337) 
(list 2165.415 820.987) 
(list 2165.415 820.81) 
(list 2239.4375 820.26)))
(apply 'command (append '("pline") coords '("c")))
(setq currobj (ssadd (entlast) currobj))
(setq coords (list 
(list 2239.4375 820.117) 
(list 2165.415 820.667) 
(list 2165.415 820.49) 
(list 2239.4375 820.04)))
(apply 'command (append '("pline") coords '("c")))
(setq currobj (ssadd (entlast) currobj))
(setq coords (list 
(list 2239.4375 819.897) 
(list 2165.415 820.347) 
(list 2165.415 820.17) 
(list 2239.4375 819.82)))
(apply 'command (append '("pline") coords '("c")))
(setq currobj (ssadd (entlast) currobj))
(setq coords (list 
(list 2239.4375 819.677) 
(list 2165.415 820.027) 
(list 2165.415 819.85) 
(list 2239.4375 819.6)))
(apply 'command (append '("pline") coords '("c")))
(setq currobj (ssadd (entlast) currobj))
(setq coords (list 
(list 2239.4375 819.457) 
(list 2165.415 819.707) 
(list 2165.415 819.53) 
(list 2239.4375 819.38)))
(apply 'command (append '("pline") coords '("c")))
(setq currobj (ssadd (entlast) currobj))
(setq coords (list 
(list 2239.4375 819.237) 
(list 2165.415 819.387) 
(list 2165.415 819.21) 
(list 2239.4375 819.16)))
(apply 'command (append '("pline") coords '("c")))
(setq currobj (ssadd (entlast) currobj))
(setq coords (list 
(list 2239.4375 819.017) 
(list 2165.415 819.067) 
(list 2165.415 818.89) 
(list 2239.4375 818.94)))
(apply 'command (append '("pline") coords '("c")))
(setq currobj (ssadd (entlast) currobj))
(setq coords (list 
(list 2239.4375 818.797) 
(list 2165.415 818.747) 
(list 2165.415 818.57) 
(list 2239.4375 818.72)))
(apply 'command (append '("pline") coords '("c")))
(setq currobj (ssadd (entlast) currobj))
(setq coords (list 
(list 2239.4375 818.577) 
(list 2165.415 818.427) 
(list 2165.415 818.25) 
(list 2239.4375 818.5)))
(apply 'command (append '("pline") coords '("c")))
(setq currobj (ssadd (entlast) currobj))
(setq coords (list 
(list 2239.4375 818.357) 
(list 2165.415 818.107) 
(list 2165.415 817.93) 
(list 2239.4375 818.28)))
(apply 'command (append '("pline") coords '("c")))
(setq currobj (ssadd (entlast) currobj))
(setq coords (list 
(list 2239.4375 818.137) 
(list 2165.415 817.787) 
(list 2165.415 817.61) 
(list 2239.4375 818.06)))
(apply 'command (append '("pline") coords '("c")))
(setq currobj (ssadd (entlast) currobj))
(setq coords (list 
(list 2239.4375 817.917) 
(list 2165.415 817.467) 
(list 2165.415 817.29) 
(list 2239.4375 817.84)))
(apply 'command (append '("pline") coords '("c")))
(setq currobj (ssadd (entlast) currobj))
(setq coords (list 
(list 2239.4375 817.697) 
(list 2165.415 817.147) 
(list 2165.415 816.97) 
(list 2239.4375 817.62)))
(apply 'command (append '("pline") coords '("c")))
(setq currobj (ssadd (entlast) currobj))
(setq coords (list 
(list 2239.4375 817.477) 
(list 2165.415 816.827) 
(list 2165.415 816.65) 
(list 2239.4375 817.4)))
(apply 'command (append '("pline") coords '("c")))
(setq currobj (ssadd (entlast) currobj))
(command "_layer" "set" "nitride" "")
(command "_layer" "set" "text" "")
(command "_circle" "2239.0625,806.257" "0.075")
(command "_circle" "2239.0625,806.557" "0.075")
(command "_circle" "2239.0625,806.857" "0.075")
(command "_circle" "2239.0625,807.157" "0.075")
(command "_circle" "2239.0625,807.457" "0.075")
(command "_circle" "2238.7625,806.257" "0.075")
(command "_circle" "2238.7625,806.557" "0.075")
(command "_circle" "2238.7625,806.857" "0.075")
(command "_circle" "2238.7625,807.157" "0.075")
(command "_circle" "2238.7625,807.457" "0.075")
(command "_circle" "2238.4625,806.257" "0.075")
(command "_circle" "2238.4625,806.557" "0.075")
(command "_circle" "2238.4625,806.857" "0.075")
(command "_circle" "2238.4625,807.157" "0.075")
(command "_circle" "2238.4625,807.457" "0.075")
(command "_circle" "2238.1625,806.257" "0.075")
(command "_circle" "2238.1625,806.557" "0.075")
(command "_circle" "2238.1625,806.857" "0.075")
(command "_circle" "2238.1625,807.157" "0.075")
(command "_circle" "2238.1625,807.457" "0.075")
(command "_circle" "2237.8625,806.257" "0.075")
(command "_circle" "2237.8625,806.557" "0.075")
(command "_circle" "2237.8625,806.857" "0.075")
(command "_circle" "2237.8625,807.157" "0.075")
(command "_circle" "2237.8625,807.457" "0.075")
(command "_layer" "set" "nitride" "")
(setq coords (list 
(list 2240.2625 831.7) 
(list 2240.2625 836.7) 
(list 2239.7375 836.7) 
(list 2239.7375 831.7)))
(apply 'command (append '("pline") coords '("c")))
(setq currobj (ssadd (entlast) currobj))
(command "_layer" "set" "prebias" "")
(command "_rectangle" "2239.7375,831.7" "2240.2625,836.7")
(setq currobj (ssadd (entlast) currobj))
(command "_layer" "set" "nitride" "")
(setq cooledsinglenanobeam7 currobj)
(setq currobj nil)
(setq currobj (ssadd))
; DRAWING PHOTONIC CRYSTAL
(command "_layer" "set" "negYjunc" "")
(setq coords (list 
(list 2240.135 866.7) 
(list 2240 851.7) 
(list 2240 866.7)))
(apply 'command (append '("pline") coords '("c")))
(setq currobj (ssadd (entlast) currobj))
(setq coords (list 
(list 2240.2625 836.7) 
(list 2240.415 866.7) 
(list 2241.096 866.7) 
(list 2241.096 836.7)))
(apply 'command (append '("pline") coords '("c")))
(setq currobj (ssadd (entlast) currobj))
(setq coords (list 
(list 2239.865 866.7) 
(list 2240 851.7) 
(list 2240 866.7)))
(apply 'command (append '("pline") coords '("c")))
(setq currobj (ssadd (entlast) currobj))
(setq coords (list 
(list 2239.7375 836.7) 
(list 2239.585 866.7) 
(list 2238.904 866.7) 
(list 2238.904 836.7)))
(apply 'command (append '("pline") coords '("c")))
(setq currobj (ssadd (entlast) currobj))
(command "_layer" "set" "nitride" "")
(setq yjunction7 currobj)
(setq currobj nil)
(setq currobj (ssadd))
(setq tap7 nil)
(setq tap7 (ssadd))
(command "_layer" "set" "phc" "")
(setq coords (list 
(list 2240 866.7) 
(list 2240.135 866.7) 
(list 2240.135 866.7103) 
(list 2240.135 866.7206) 
(list 2240.135 866.7308) 
(list 2240.135 866.7411) 
(list 2240.135 866.7514) 
(list 2240.135 866.7617) 
(list 2240.135 866.7719) 
(list 2240.135 866.7822) 
(list 2240.135 866.7925) 
(list 2240.135 866.8028) 
(list 2240.135 866.8131) 
(list 2240.135 866.8233) 
(list 2240.135 866.8336) 
(list 2240.135 866.8439) 
(list 2240.135 866.8542) 
(list 2240.135 866.8644) 
(list 2240.135 866.8747) 
(list 2240.135 866.885) 
(list 2240.135 866.8953) 
(list 2240.135 866.9056) 
(list 2240.135 866.9158) 
(list 2240.135 866.9261) 
(list 2240.135 866.9364) 
(list 2240.135 866.9467) 
(list 2240.135 866.9569) 
(list 2240.135 866.9672) 
(list 2240.135 866.9775) 
(list 2240.135 866.9878) 
(list 2240.135 866.9981) 
(list 2240.135 867.0083) 
(list 2240.135 867.0186) 
(list 2240.135 867.0289) 
(list 2240.135 867.0392) 
(list 2240.135 867.0494) 
(list 2240.135 867.0597) 
(list 2240.135 867.07) 
(list 2240 867.07)))
(apply 'command (append '("pline") coords '("c")))
(setq tap7 (ssadd (entlast) tap7))
(command "_mirror" (entlast) "" "2240,900" "2240,901" "No")
(setq tap7 (ssadd (entlast) tap7))
(setq coords (list 
(list 2240.4239 866.7) 
(list 2240.415 866.7) 
(list 2240.4152 866.7103) 
(list 2240.4155 866.7206) 
(list 2240.4156 866.7308) 
(list 2240.4158 866.7411) 
(list 2240.4158 866.7514) 
(list 2240.4157 866.7617) 
(list 2240.4156 866.7719) 
(list 2240.4154 866.7822) 
(list 2240.415 866.7925) 
(list 2240.4146 866.8028) 
(list 2240.4141 866.8131) 
(list 2240.4136 866.8233) 
(list 2240.413 866.8336) 
(list 2240.4124 866.8439) 
(list 2240.4119 866.8542) 
(list 2240.4114 866.8644) 
(list 2240.4109 866.8747) 
(list 2240.4106 866.885) 
(list 2240.4105 866.8953) 
(list 2240.4104 866.9056) 
(list 2240.4106 866.9158) 
(list 2240.4109 866.9261) 
(list 2240.4114 866.9364) 
(list 2240.4121 866.9467) 
(list 2240.413 866.9569) 
(list 2240.4139 866.9672) 
(list 2240.4151 866.9775) 
(list 2240.4162 866.9878) 
(list 2240.4175 866.9981) 
(list 2240.4187 867.0083) 
(list 2240.4199 867.0186) 
(list 2240.4211 867.0289) 
(list 2240.422 867.0392) 
(list 2240.4229 867.0494) 
(list 2240.4235 867.0597) 
(list 2240.4239 867.07) 
(list 2240.4239 867.07)))
(apply 'command (append '("pline") coords '("c")))
(setq tap7 (ssadd (entlast) tap7))
(command "_mirror" (entlast) "" "2240,900" "2240,901" "No")
(setq tap7 (ssadd (entlast) tap7))
(setq coords (list 
(list 2241.096 866.7) 
(list 2240.4239 866.7) 
(list 2240.4239 866.7103) 
(list 2240.4239 866.7206) 
(list 2240.4239 866.7308) 
(list 2240.4239 866.7411) 
(list 2240.4239 866.7514) 
(list 2240.4239 866.7617) 
(list 2240.4239 866.7719) 
(list 2240.4239 866.7822) 
(list 2240.4239 866.7925) 
(list 2240.4239 866.8028) 
(list 2240.4239 866.8131) 
(list 2240.4239 866.8233) 
(list 2240.4239 866.8336) 
(list 2240.4239 866.8439) 
(list 2240.4239 866.8542) 
(list 2240.4239 866.8644) 
(list 2240.4239 866.8747) 
(list 2240.4239 866.885) 
(list 2240.4239 866.8953) 
(list 2240.4239 866.9056) 
(list 2240.4239 866.9158) 
(list 2240.4239 866.9261) 
(list 2240.4239 866.9364) 
(list 2240.4239 866.9467) 
(list 2240.4239 866.9569) 
(list 2240.4239 866.9672) 
(list 2240.4239 866.9775) 
(list 2240.4239 866.9878) 
(list 2240.4239 866.9981) 
(list 2240.4239 867.0083) 
(list 2240.4239 867.0186) 
(list 2240.4239 867.0289) 
(list 2240.4239 867.0392) 
(list 2240.4239 867.0494) 
(list 2240.4239 867.0597) 
(list 2240.4239 867.07) 
(list 2241.096 867.07)))
(apply 'command (append '("pline") coords '("c")))
(setq tap7 (ssadd (entlast) tap7))
(command "_mirror" (entlast) "" "2240,900" "2240,901" "No")
(setq tap7 (ssadd (entlast) tap7))
(setq coords (list 
(list 2240 867.07) 
(list 2240.135 867.07) 
(list 2240.135 867.0803) 
(list 2240.135 867.0906) 
(list 2240.135 867.1008) 
(list 2240.135 867.1111) 
(list 2240.135 867.1214) 
(list 2240.135 867.1317) 
(list 2240.135 867.1419) 
(list 2240.135 867.1522) 
(list 2240.135 867.1625) 
(list 2240.135 867.1728) 
(list 2240.135 867.1831) 
(list 2240.135 867.1933) 
(list 2240.135 867.2036) 
(list 2240.135 867.2139) 
(list 2240.135 867.2242) 
(list 2240.135 867.2344) 
(list 2240.135 867.2447) 
(list 2240.135 867.255) 
(list 2240.135 867.2653) 
(list 2240.135 867.2756) 
(list 2240.135 867.2858) 
(list 2240.135 867.2961) 
(list 2240.135 867.3064) 
(list 2240.135 867.3167) 
(list 2240.135 867.3269) 
(list 2240.135 867.3372) 
(list 2240.135 867.3475) 
(list 2240.135 867.3578) 
(list 2240.135 867.3681) 
(list 2240.135 867.3783) 
(list 2240.135 867.3886) 
(list 2240.135 867.3989) 
(list 2240.135 867.4092) 
(list 2240.135 867.4194) 
(list 2240.135 867.4297) 
(list 2240.135 867.44) 
(list 2240 867.44)))
(apply 'command (append '("pline") coords '("c")))
(setq tap7 (ssadd (entlast) tap7))
(command "_mirror" (entlast) "" "2240,900" "2240,901" "No")
(setq tap7 (ssadd (entlast) tap7))
(setq coords (list 
(list 2240.4327 867.07) 
(list 2240.4239 867.07) 
(list 2240.424 867.0803) 
(list 2240.4238 867.0906) 
(list 2240.4233 867.1008) 
(list 2240.4226 867.1111) 
(list 2240.4215 867.1214) 
(list 2240.4202 867.1317) 
(list 2240.4187 867.1419) 
(list 2240.4169 867.1522) 
(list 2240.4151 867.1625) 
(list 2240.4131 867.1728) 
(list 2240.4112 867.1831) 
(list 2240.4092 867.1933) 
(list 2240.4074 867.2036) 
(list 2240.4057 867.2139) 
(list 2240.4043 867.2242) 
(list 2240.4032 867.2344) 
(list 2240.4023 867.2447) 
(list 2240.4019 867.255) 
(list 2240.4019 867.2653) 
(list 2240.4022 867.2756) 
(list 2240.403 867.2858) 
(list 2240.4042 867.2961) 
(list 2240.4058 867.3064) 
(list 2240.4078 867.3167) 
(list 2240.41 867.3269) 
(list 2240.4125 867.3372) 
(list 2240.4151 867.3475) 
(list 2240.4178 867.3578) 
(list 2240.4206 867.3681) 
(list 2240.4232 867.3783) 
(list 2240.4257 867.3886) 
(list 2240.4279 867.3989) 
(list 2240.4297 867.4092) 
(list 2240.4312 867.4194) 
(list 2240.4322 867.4297) 
(list 2240.4327 867.44) 
(list 2240.4327 867.44)))
(apply 'command (append '("pline") coords '("c")))
(setq tap7 (ssadd (entlast) tap7))
(command "_mirror" (entlast) "" "2240,900" "2240,901" "No")
(setq tap7 (ssadd (entlast) tap7))
(setq coords (list 
(list 2241.096 867.07) 
(list 2240.4327 867.07) 
(list 2240.4327 867.0803) 
(list 2240.4327 867.0906) 
(list 2240.4327 867.1008) 
(list 2240.4327 867.1111) 
(list 2240.4327 867.1214) 
(list 2240.4327 867.1317) 
(list 2240.4327 867.1419) 
(list 2240.4327 867.1522) 
(list 2240.4327 867.1625) 
(list 2240.4327 867.1728) 
(list 2240.4327 867.1831) 
(list 2240.4327 867.1933) 
(list 2240.4327 867.2036) 
(list 2240.4327 867.2139) 
(list 2240.4327 867.2242) 
(list 2240.4327 867.2344) 
(list 2240.4327 867.2447) 
(list 2240.4327 867.255) 
(list 2240.4327 867.2653) 
(list 2240.4327 867.2756) 
(list 2240.4327 867.2858) 
(list 2240.4327 867.2961) 
(list 2240.4327 867.3064) 
(list 2240.4327 867.3167) 
(list 2240.4327 867.3269) 
(list 2240.4327 867.3372) 
(list 2240.4327 867.3475) 
(list 2240.4327 867.3578) 
(list 2240.4327 867.3681) 
(list 2240.4327 867.3783) 
(list 2240.4327 867.3886) 
(list 2240.4327 867.3989) 
(list 2240.4327 867.4092) 
(list 2240.4327 867.4194) 
(list 2240.4327 867.4297) 
(list 2240.4327 867.44) 
(list 2241.096 867.44)))
(apply 'command (append '("pline") coords '("c")))
(setq tap7 (ssadd (entlast) tap7))
(command "_mirror" (entlast) "" "2240,900" "2240,901" "No")
(setq tap7 (ssadd (entlast) tap7))
(setq coords (list 
(list 2240 867.44) 
(list 2240.135 867.44) 
(list 2240.135 867.4503) 
(list 2240.135 867.4606) 
(list 2240.135 867.4708) 
(list 2240.135 867.4811) 
(list 2240.135 867.4914) 
(list 2240.135 867.5017) 
(list 2240.135 867.5119) 
(list 2240.135 867.5222) 
(list 2240.135 867.5325) 
(list 2240.135 867.5428) 
(list 2240.135 867.5531) 
(list 2240.135 867.5633) 
(list 2240.135 867.5736) 
(list 2240.135 867.5839) 
(list 2240.135 867.5942) 
(list 2240.135 867.6044) 
(list 2240.135 867.6147) 
(list 2240.135 867.625) 
(list 2240.135 867.6353) 
(list 2240.135 867.6456) 
(list 2240.135 867.6558) 
(list 2240.135 867.6661) 
(list 2240.135 867.6764) 
(list 2240.135 867.6867) 
(list 2240.135 867.6969) 
(list 2240.135 867.7072) 
(list 2240.135 867.7175) 
(list 2240.135 867.7278) 
(list 2240.135 867.7381) 
(list 2240.135 867.7483) 
(list 2240.135 867.7586) 
(list 2240.135 867.7689) 
(list 2240.135 867.7792) 
(list 2240.135 867.7894) 
(list 2240.135 867.7997) 
(list 2240.135 867.81) 
(list 2240 867.81)))
(apply 'command (append '("pline") coords '("c")))
(setq tap7 (ssadd (entlast) tap7))
(command "_mirror" (entlast) "" "2240,900" "2240,901" "No")
(setq tap7 (ssadd (entlast) tap7))
(setq coords (list 
(list 2240.4416 867.44) 
(list 2240.4327 867.44) 
(list 2240.4327 867.4503) 
(list 2240.4321 867.4606) 
(list 2240.431 867.4708) 
(list 2240.4294 867.4811) 
(list 2240.4272 867.4914) 
(list 2240.4247 867.5017) 
(list 2240.4218 867.5119) 
(list 2240.4185 867.5222) 
(list 2240.4151 867.5325) 
(list 2240.4117 867.5428) 
(list 2240.4082 867.5531) 
(list 2240.4049 867.5633) 
(list 2240.4018 867.5736) 
(list 2240.3991 867.5839) 
(list 2240.3967 867.5942) 
(list 2240.3949 867.6044) 
(list 2240.3937 867.6147) 
(list 2240.3932 867.625) 
(list 2240.3933 867.6353) 
(list 2240.394 867.6456) 
(list 2240.3955 867.6558) 
(list 2240.3976 867.6661) 
(list 2240.4002 867.6764) 
(list 2240.4034 867.6867) 
(list 2240.4071 867.6969) 
(list 2240.411 867.7072) 
(list 2240.4152 867.7175) 
(list 2240.4194 867.7278) 
(list 2240.4236 867.7381) 
(list 2240.4277 867.7483) 
(list 2240.4314 867.7586) 
(list 2240.4347 867.7689) 
(list 2240.4374 867.7792) 
(list 2240.4395 867.7894) 
(list 2240.441 867.7997) 
(list 2240.4416 867.81) 
(list 2240.4416 867.81)))
(apply 'command (append '("pline") coords '("c")))
(setq tap7 (ssadd (entlast) tap7))
(command "_mirror" (entlast) "" "2240,900" "2240,901" "No")
(setq tap7 (ssadd (entlast) tap7))
(setq coords (list 
(list 2241.096 867.44) 
(list 2240.4416 867.44) 
(list 2240.4416 867.4503) 
(list 2240.4416 867.4606) 
(list 2240.4416 867.4708) 
(list 2240.4416 867.4811) 
(list 2240.4416 867.4914) 
(list 2240.4416 867.5017) 
(list 2240.4416 867.5119) 
(list 2240.4416 867.5222) 
(list 2240.4416 867.5325) 
(list 2240.4416 867.5428) 
(list 2240.4416 867.5531) 
(list 2240.4416 867.5633) 
(list 2240.4416 867.5736) 
(list 2240.4416 867.5839) 
(list 2240.4416 867.5942) 
(list 2240.4416 867.6044) 
(list 2240.4416 867.6147) 
(list 2240.4416 867.625) 
(list 2240.4416 867.6353) 
(list 2240.4416 867.6456) 
(list 2240.4416 867.6558) 
(list 2240.4416 867.6661) 
(list 2240.4416 867.6764) 
(list 2240.4416 867.6867) 
(list 2240.4416 867.6969) 
(list 2240.4416 867.7072) 
(list 2240.4416 867.7175) 
(list 2240.4416 867.7278) 
(list 2240.4416 867.7381) 
(list 2240.4416 867.7483) 
(list 2240.4416 867.7586) 
(list 2240.4416 867.7689) 
(list 2240.4416 867.7792) 
(list 2240.4416 867.7894) 
(list 2240.4416 867.7997) 
(list 2240.4416 867.81) 
(list 2241.096 867.81)))
(apply 'command (append '("pline") coords '("c")))
(setq tap7 (ssadd (entlast) tap7))
(command "_mirror" (entlast) "" "2240,900" "2240,901" "No")
(setq tap7 (ssadd (entlast) tap7))
(setq coords (list 
(list 2240 867.81) 
(list 2240.135 867.81) 
(list 2240.135 867.8203) 
(list 2240.135 867.8306) 
(list 2240.135 867.8408) 
(list 2240.135 867.8511) 
(list 2240.135 867.8614) 
(list 2240.135 867.8717) 
(list 2240.135 867.8819) 
(list 2240.135 867.8922) 
(list 2240.135 867.9025) 
(list 2240.135 867.9128) 
(list 2240.135 867.9231) 
(list 2240.135 867.9333) 
(list 2240.135 867.9436) 
(list 2240.135 867.9539) 
(list 2240.135 867.9642) 
(list 2240.135 867.9744) 
(list 2240.135 867.9847) 
(list 2240.135 867.995) 
(list 2240.135 868.0053) 
(list 2240.135 868.0156) 
(list 2240.135 868.0258) 
(list 2240.135 868.0361) 
(list 2240.135 868.0464) 
(list 2240.135 868.0567) 
(list 2240.135 868.0669) 
(list 2240.135 868.0772) 
(list 2240.135 868.0875) 
(list 2240.135 868.0978) 
(list 2240.135 868.1081) 
(list 2240.135 868.1183) 
(list 2240.135 868.1286) 
(list 2240.135 868.1389) 
(list 2240.135 868.1492) 
(list 2240.135 868.1594) 
(list 2240.135 868.1697) 
(list 2240.135 868.18) 
(list 2240 868.18)))
(apply 'command (append '("pline") coords '("c")))
(setq tap7 (ssadd (entlast) tap7))
(command "_mirror" (entlast) "" "2240,900" "2240,901" "No")
(setq tap7 (ssadd (entlast) tap7))
(setq coords (list 
(list 2240.4505 867.81) 
(list 2240.4416 867.81) 
(list 2240.4414 867.8203) 
(list 2240.4405 867.8306) 
(list 2240.4387 867.8408) 
(list 2240.4362 867.8511) 
(list 2240.433 867.8614) 
(list 2240.4291 867.8717) 
(list 2240.4248 867.8819) 
(list 2240.4201 867.8922) 
(list 2240.4152 867.9025) 
(list 2240.4102 867.9128) 
(list 2240.4053 867.9231) 
(list 2240.4006 867.9333) 
(list 2240.3962 867.9436) 
(list 2240.3924 867.9539) 
(list 2240.3892 867.9642) 
(list 2240.3867 867.9744) 
(list 2240.3851 867.9847) 
(list 2240.3844 867.995) 
(list 2240.3847 868.0053) 
(list 2240.3858 868.0156) 
(list 2240.3879 868.0258) 
(list 2240.3909 868.0361) 
(list 2240.3947 868.0464) 
(list 2240.3991 868.0567) 
(list 2240.4041 868.0669) 
(list 2240.4096 868.0772) 
(list 2240.4153 868.0875) 
(list 2240.421 868.0978) 
(list 2240.4267 868.1081) 
(list 2240.4321 868.1183) 
(list 2240.4371 868.1286) 
(list 2240.4415 868.1389) 
(list 2240.4451 868.1492) 
(list 2240.4479 868.1594) 
(list 2240.4497 868.1697) 
(list 2240.4505 868.18) 
(list 2240.4505 868.18)))
(apply 'command (append '("pline") coords '("c")))
(setq tap7 (ssadd (entlast) tap7))
(command "_mirror" (entlast) "" "2240,900" "2240,901" "No")
(setq tap7 (ssadd (entlast) tap7))
(setq coords (list 
(list 2241.096 867.81) 
(list 2240.4505 867.81) 
(list 2240.4505 867.8203) 
(list 2240.4505 867.8306) 
(list 2240.4505 867.8408) 
(list 2240.4505 867.8511) 
(list 2240.4505 867.8614) 
(list 2240.4505 867.8717) 
(list 2240.4505 867.8819) 
(list 2240.4505 867.8922) 
(list 2240.4505 867.9025) 
(list 2240.4505 867.9128) 
(list 2240.4505 867.9231) 
(list 2240.4505 867.9333) 
(list 2240.4505 867.9436) 
(list 2240.4505 867.9539) 
(list 2240.4505 867.9642) 
(list 2240.4505 867.9744) 
(list 2240.4505 867.9847) 
(list 2240.4505 867.995) 
(list 2240.4505 868.0053) 
(list 2240.4505 868.0156) 
(list 2240.4505 868.0258) 
(list 2240.4505 868.0361) 
(list 2240.4505 868.0464) 
(list 2240.4505 868.0567) 
(list 2240.4505 868.0669) 
(list 2240.4505 868.0772) 
(list 2240.4505 868.0875) 
(list 2240.4505 868.0978) 
(list 2240.4505 868.1081) 
(list 2240.4505 868.1183) 
(list 2240.4505 868.1286) 
(list 2240.4505 868.1389) 
(list 2240.4505 868.1492) 
(list 2240.4505 868.1594) 
(list 2240.4505 868.1697) 
(list 2240.4505 868.18) 
(list 2241.096 868.18)))
(apply 'command (append '("pline") coords '("c")))
(setq tap7 (ssadd (entlast) tap7))
(command "_mirror" (entlast) "" "2240,900" "2240,901" "No")
(setq tap7 (ssadd (entlast) tap7))
(setq coords (list 
(list 2240 868.18) 
(list 2240.135 868.18) 
(list 2240.135 868.1903) 
(list 2240.135 868.2006) 
(list 2240.135 868.2108) 
(list 2240.135 868.2211) 
(list 2240.135 868.2314) 
(list 2240.135 868.2417) 
(list 2240.135 868.2519) 
(list 2240.135 868.2622) 
(list 2240.135 868.2725) 
(list 2240.135 868.2828) 
(list 2240.135 868.2931) 
(list 2240.135 868.3033) 
(list 2240.135 868.3136) 
(list 2240.135 868.3239) 
(list 2240.135 868.3342) 
(list 2240.135 868.3444) 
(list 2240.135 868.3547) 
(list 2240.135 868.365) 
(list 2240.135 868.3753) 
(list 2240.135 868.3856) 
(list 2240.135 868.3958) 
(list 2240.135 868.4061) 
(list 2240.135 868.4164) 
(list 2240.135 868.4267) 
(list 2240.135 868.4369) 
(list 2240.135 868.4472) 
(list 2240.135 868.4575) 
(list 2240.135 868.4678) 
(list 2240.135 868.4781) 
(list 2240.135 868.4883) 
(list 2240.135 868.4986) 
(list 2240.135 868.5089) 
(list 2240.135 868.5192) 
(list 2240.135 868.5294) 
(list 2240.135 868.5397) 
(list 2240.135 868.55) 
(list 2240 868.55)))
(apply 'command (append '("pline") coords '("c")))
(setq tap7 (ssadd (entlast) tap7))
(command "_mirror" (entlast) "" "2240,900" "2240,901" "No")
(setq tap7 (ssadd (entlast) tap7))
(setq coords (list 
(list 2240.4593 868.18) 
(list 2240.4505 868.18) 
(list 2240.4502 868.1903) 
(list 2240.4488 868.2006) 
(list 2240.4464 868.2108) 
(list 2240.443 868.2211) 
(list 2240.4387 868.2314) 
(list 2240.4336 868.2417) 
(list 2240.4279 868.2519) 
(list 2240.4217 868.2622) 
(list 2240.4153 868.2725) 
(list 2240.4087 868.2828) 
(list 2240.4023 868.2931) 
(list 2240.3962 868.3033) 
(list 2240.3906 868.3136) 
(list 2240.3857 868.3239) 
(list 2240.3816 868.3342) 
(list 2240.3785 868.3444) 
(list 2240.3765 868.3547) 
(list 2240.3757 868.365) 
(list 2240.3761 868.3753) 
(list 2240.3776 868.3856) 
(list 2240.3804 868.3958) 
(list 2240.3842 868.4061) 
(list 2240.3891 868.4164) 
(list 2240.3948 868.4267) 
(list 2240.4012 868.4369) 
(list 2240.4081 868.4472) 
(list 2240.4153 868.4575) 
(list 2240.4226 868.4678) 
(list 2240.4298 868.4781) 
(list 2240.4366 868.4883) 
(list 2240.4428 868.4986) 
(list 2240.4483 868.5089) 
(list 2240.4528 868.5192) 
(list 2240.4562 868.5294) 
(list 2240.4584 868.5397) 
(list 2240.4593 868.55) 
(list 2240.4593 868.55)))
(apply 'command (append '("pline") coords '("c")))
(setq tap7 (ssadd (entlast) tap7))
(command "_mirror" (entlast) "" "2240,900" "2240,901" "No")
(setq tap7 (ssadd (entlast) tap7))
(setq coords (list 
(list 2241.096 868.18) 
(list 2240.4593 868.18) 
(list 2240.4593 868.1903) 
(list 2240.4593 868.2006) 
(list 2240.4593 868.2108) 
(list 2240.4593 868.2211) 
(list 2240.4593 868.2314) 
(list 2240.4593 868.2417) 
(list 2240.4593 868.2519) 
(list 2240.4593 868.2622) 
(list 2240.4593 868.2725) 
(list 2240.4593 868.2828) 
(list 2240.4593 868.2931) 
(list 2240.4593 868.3033) 
(list 2240.4593 868.3136) 
(list 2240.4593 868.3239) 
(list 2240.4593 868.3342) 
(list 2240.4593 868.3444) 
(list 2240.4593 868.3547) 
(list 2240.4593 868.365) 
(list 2240.4593 868.3753) 
(list 2240.4593 868.3856) 
(list 2240.4593 868.3958) 
(list 2240.4593 868.4061) 
(list 2240.4593 868.4164) 
(list 2240.4593 868.4267) 
(list 2240.4593 868.4369) 
(list 2240.4593 868.4472) 
(list 2240.4593 868.4575) 
(list 2240.4593 868.4678) 
(list 2240.4593 868.4781) 
(list 2240.4593 868.4883) 
(list 2240.4593 868.4986) 
(list 2240.4593 868.5089) 
(list 2240.4593 868.5192) 
(list 2240.4593 868.5294) 
(list 2240.4593 868.5397) 
(list 2240.4593 868.55) 
(list 2241.096 868.55)))
(apply 'command (append '("pline") coords '("c")))
(setq tap7 (ssadd (entlast) tap7))
(command "_mirror" (entlast) "" "2240,900" "2240,901" "No")
(setq tap7 (ssadd (entlast) tap7))
(setq coords (list 
(list 2240 868.55) 
(list 2240.135 868.55) 
(list 2240.135 868.5603) 
(list 2240.135 868.5706) 
(list 2240.135 868.5808) 
(list 2240.135 868.5911) 
(list 2240.135 868.6014) 
(list 2240.135 868.6117) 
(list 2240.135 868.6219) 
(list 2240.135 868.6322) 
(list 2240.135 868.6425) 
(list 2240.135 868.6528) 
(list 2240.135 868.6631) 
(list 2240.135 868.6733) 
(list 2240.135 868.6836) 
(list 2240.135 868.6939) 
(list 2240.135 868.7042) 
(list 2240.135 868.7144) 
(list 2240.135 868.7247) 
(list 2240.135 868.735) 
(list 2240.135 868.7453) 
(list 2240.135 868.7556) 
(list 2240.135 868.7658) 
(list 2240.135 868.7761) 
(list 2240.135 868.7864) 
(list 2240.135 868.7967) 
(list 2240.135 868.8069) 
(list 2240.135 868.8172) 
(list 2240.135 868.8275) 
(list 2240.135 868.8378) 
(list 2240.135 868.8481) 
(list 2240.135 868.8583) 
(list 2240.135 868.8686) 
(list 2240.135 868.8789) 
(list 2240.135 868.8892) 
(list 2240.135 868.8994) 
(list 2240.135 868.9097) 
(list 2240.135 868.92) 
(list 2240 868.92)))
(apply 'command (append '("pline") coords '("c")))
(setq tap7 (ssadd (entlast) tap7))
(command "_mirror" (entlast) "" "2240,900" "2240,901" "No")
(setq tap7 (ssadd (entlast) tap7))
(setq coords (list 
(list 2240.4682 868.55) 
(list 2240.4593 868.55) 
(list 2240.4589 868.5603) 
(list 2240.4571 868.5706) 
(list 2240.4541 868.5808) 
(list 2240.4498 868.5911) 
(list 2240.4444 868.6014) 
(list 2240.4381 868.6117) 
(list 2240.431 868.6219) 
(list 2240.4233 868.6322) 
(list 2240.4154 868.6425) 
(list 2240.4073 868.6528) 
(list 2240.3994 868.6631) 
(list 2240.3919 868.6733) 
(list 2240.385 868.6836) 
(list 2240.379 868.6939) 
(list 2240.3741 868.7042) 
(list 2240.3703 868.7144) 
(list 2240.3679 868.7247) 
(list 2240.367 868.735) 
(list 2240.3675 868.7453) 
(list 2240.3694 868.7556) 
(list 2240.3728 868.7658) 
(list 2240.3775 868.7761) 
(list 2240.3835 868.7864) 
(list 2240.3904 868.7967) 
(list 2240.3982 868.8069) 
(list 2240.4066 868.8172) 
(list 2240.4154 868.8275) 
(list 2240.4242 868.8378) 
(list 2240.4329 868.8481) 
(list 2240.4411 868.8583) 
(list 2240.4485 868.8686) 
(list 2240.4551 868.8789) 
(list 2240.4605 868.8892) 
(list 2240.4646 868.8994) 
(list 2240.4672 868.9097) 
(list 2240.4682 868.92) 
(list 2240.4682 868.92)))
(apply 'command (append '("pline") coords '("c")))
(setq tap7 (ssadd (entlast) tap7))
(command "_mirror" (entlast) "" "2240,900" "2240,901" "No")
(setq tap7 (ssadd (entlast) tap7))
(setq coords (list 
(list 2241.096 868.55) 
(list 2240.4682 868.55) 
(list 2240.4682 868.5603) 
(list 2240.4682 868.5706) 
(list 2240.4682 868.5808) 
(list 2240.4682 868.5911) 
(list 2240.4682 868.6014) 
(list 2240.4682 868.6117) 
(list 2240.4682 868.6219) 
(list 2240.4682 868.6322) 
(list 2240.4682 868.6425) 
(list 2240.4682 868.6528) 
(list 2240.4682 868.6631) 
(list 2240.4682 868.6733) 
(list 2240.4682 868.6836) 
(list 2240.4682 868.6939) 
(list 2240.4682 868.7042) 
(list 2240.4682 868.7144) 
(list 2240.4682 868.7247) 
(list 2240.4682 868.735) 
(list 2240.4682 868.7453) 
(list 2240.4682 868.7556) 
(list 2240.4682 868.7658) 
(list 2240.4682 868.7761) 
(list 2240.4682 868.7864) 
(list 2240.4682 868.7967) 
(list 2240.4682 868.8069) 
(list 2240.4682 868.8172) 
(list 2240.4682 868.8275) 
(list 2240.4682 868.8378) 
(list 2240.4682 868.8481) 
(list 2240.4682 868.8583) 
(list 2240.4682 868.8686) 
(list 2240.4682 868.8789) 
(list 2240.4682 868.8892) 
(list 2240.4682 868.8994) 
(list 2240.4682 868.9097) 
(list 2240.4682 868.92) 
(list 2241.096 868.92)))
(apply 'command (append '("pline") coords '("c")))
(setq tap7 (ssadd (entlast) tap7))
(command "_mirror" (entlast) "" "2240,900" "2240,901" "No")
(setq tap7 (ssadd (entlast) tap7))
(setq coords (list 
(list 2240 868.92) 
(list 2240.135 868.92) 
(list 2240.135 868.9303) 
(list 2240.135 868.9406) 
(list 2240.135 868.9508) 
(list 2240.135 868.9611) 
(list 2240.135 868.9714) 
(list 2240.135 868.9817) 
(list 2240.135 868.9919) 
(list 2240.135 869.0022) 
(list 2240.135 869.0125) 
(list 2240.135 869.0228) 
(list 2240.135 869.0331) 
(list 2240.135 869.0433) 
(list 2240.135 869.0536) 
(list 2240.135 869.0639) 
(list 2240.135 869.0742) 
(list 2240.135 869.0844) 
(list 2240.135 869.0947) 
(list 2240.135 869.105) 
(list 2240.135 869.1153) 
(list 2240.135 869.1256) 
(list 2240.135 869.1358) 
(list 2240.135 869.1461) 
(list 2240.135 869.1564) 
(list 2240.135 869.1667) 
(list 2240.135 869.1769) 
(list 2240.135 869.1872) 
(list 2240.135 869.1975) 
(list 2240.135 869.2078) 
(list 2240.135 869.2181) 
(list 2240.135 869.2283) 
(list 2240.135 869.2386) 
(list 2240.135 869.2489) 
(list 2240.135 869.2592) 
(list 2240.135 869.2694) 
(list 2240.135 869.2797) 
(list 2240.135 869.29) 
(list 2240 869.29)))
(apply 'command (append '("pline") coords '("c")))
(setq tap7 (ssadd (entlast) tap7))
(command "_mirror" (entlast) "" "2240,900" "2240,901" "No")
(setq tap7 (ssadd (entlast) tap7))
(setq coords (list 
(list 2240.4771 868.92) 
(list 2240.4682 868.92) 
(list 2240.4676 868.9303) 
(list 2240.4655 868.9406) 
(list 2240.4618 868.9508) 
(list 2240.4566 868.9611) 
(list 2240.4501 868.9714) 
(list 2240.4425 868.9817) 
(list 2240.4341 868.9919) 
(list 2240.4249 869.0022) 
(list 2240.4154 869.0125) 
(list 2240.4058 869.0228) 
(list 2240.3964 869.0331) 
(list 2240.3876 869.0433) 
(list 2240.3794 869.0536) 
(list 2240.3724 869.0639) 
(list 2240.3665 869.0742) 
(list 2240.3621 869.0844) 
(list 2240.3593 869.0947) 
(list 2240.3582 869.105) 
(list 2240.3589 869.1153) 
(list 2240.3612 869.1256) 
(list 2240.3653 869.1358) 
(list 2240.3709 869.1461) 
(list 2240.3779 869.1564) 
(list 2240.3861 869.1667) 
(list 2240.3953 869.1769) 
(list 2240.4052 869.1872) 
(list 2240.4154 869.1975) 
(list 2240.4258 869.2078) 
(list 2240.4359 869.2181) 
(list 2240.4455 869.2283) 
(list 2240.4543 869.2386) 
(list 2240.4619 869.2489) 
(list 2240.4682 869.2592) 
(list 2240.4729 869.2694) 
(list 2240.4759 869.2797) 
(list 2240.4771 869.29) 
(list 2240.4771 869.29)))
(apply 'command (append '("pline") coords '("c")))
(setq tap7 (ssadd (entlast) tap7))
(command "_mirror" (entlast) "" "2240,900" "2240,901" "No")
(setq tap7 (ssadd (entlast) tap7))
(setq coords (list 
(list 2241.096 868.92) 
(list 2240.4771 868.92) 
(list 2240.4771 868.9303) 
(list 2240.4771 868.9406) 
(list 2240.4771 868.9508) 
(list 2240.4771 868.9611) 
(list 2240.4771 868.9714) 
(list 2240.4771 868.9817) 
(list 2240.4771 868.9919) 
(list 2240.4771 869.0022) 
(list 2240.4771 869.0125) 
(list 2240.4771 869.0228) 
(list 2240.4771 869.0331) 
(list 2240.4771 869.0433) 
(list 2240.4771 869.0536) 
(list 2240.4771 869.0639) 
(list 2240.4771 869.0742) 
(list 2240.4771 869.0844) 
(list 2240.4771 869.0947) 
(list 2240.4771 869.105) 
(list 2240.4771 869.1153) 
(list 2240.4771 869.1256) 
(list 2240.4771 869.1358) 
(list 2240.4771 869.1461) 
(list 2240.4771 869.1564) 
(list 2240.4771 869.1667) 
(list 2240.4771 869.1769) 
(list 2240.4771 869.1872) 
(list 2240.4771 869.1975) 
(list 2240.4771 869.2078) 
(list 2240.4771 869.2181) 
(list 2240.4771 869.2283) 
(list 2240.4771 869.2386) 
(list 2240.4771 869.2489) 
(list 2240.4771 869.2592) 
(list 2240.4771 869.2694) 
(list 2240.4771 869.2797) 
(list 2240.4771 869.29) 
(list 2241.096 869.29)))
(apply 'command (append '("pline") coords '("c")))
(setq tap7 (ssadd (entlast) tap7))
(command "_mirror" (entlast) "" "2240,900" "2240,901" "No")
(setq tap7 (ssadd (entlast) tap7))
(setq coords (list 
(list 2240 869.29) 
(list 2240.135 869.29) 
(list 2240.135 869.3003) 
(list 2240.135 869.3106) 
(list 2240.135 869.3208) 
(list 2240.135 869.3311) 
(list 2240.135 869.3414) 
(list 2240.135 869.3517) 
(list 2240.135 869.3619) 
(list 2240.135 869.3722) 
(list 2240.135 869.3825) 
(list 2240.135 869.3928) 
(list 2240.135 869.4031) 
(list 2240.135 869.4133) 
(list 2240.135 869.4236) 
(list 2240.135 869.4339) 
(list 2240.135 869.4442) 
(list 2240.135 869.4544) 
(list 2240.135 869.4647) 
(list 2240.135 869.475) 
(list 2240.135 869.4853) 
(list 2240.135 869.4956) 
(list 2240.135 869.5058) 
(list 2240.135 869.5161) 
(list 2240.135 869.5264) 
(list 2240.135 869.5367) 
(list 2240.135 869.5469) 
(list 2240.135 869.5572) 
(list 2240.135 869.5675) 
(list 2240.135 869.5778) 
(list 2240.135 869.5881) 
(list 2240.135 869.5983) 
(list 2240.135 869.6086) 
(list 2240.135 869.6189) 
(list 2240.135 869.6292) 
(list 2240.135 869.6394) 
(list 2240.135 869.6497) 
(list 2240.135 869.66) 
(list 2240 869.66)))
(apply 'command (append '("pline") coords '("c")))
(setq tap7 (ssadd (entlast) tap7))
(command "_mirror" (entlast) "" "2240,900" "2240,901" "No")
(setq tap7 (ssadd (entlast) tap7))
(setq coords (list 
(list 2240.4859 869.29) 
(list 2240.4771 869.29) 
(list 2240.4764 869.3003) 
(list 2240.4738 869.3106) 
(list 2240.4695 869.3208) 
(list 2240.4634 869.3311) 
(list 2240.4559 869.3414) 
(list 2240.447 869.3517) 
(list 2240.4371 869.3619) 
(list 2240.4265 869.3722) 
(list 2240.4155 869.3825) 
(list 2240.4044 869.3928) 
(list 2240.3935 869.4031) 
(list 2240.3832 869.4133) 
(list 2240.3739 869.4236) 
(list 2240.3657 869.4339) 
(list 2240.359 869.4442) 
(list 2240.3539 869.4544) 
(list 2240.3507 869.4647) 
(list 2240.3495 869.475) 
(list 2240.3503 869.4853) 
(list 2240.353 869.4956) 
(list 2240.3577 869.5058) 
(list 2240.3642 869.5161) 
(list 2240.3723 869.5264) 
(list 2240.3818 869.5367) 
(list 2240.3924 869.5469) 
(list 2240.4037 869.5572) 
(list 2240.4155 869.5675) 
(list 2240.4274 869.5778) 
(list 2240.439 869.5881) 
(list 2240.45 869.5983) 
(list 2240.46 869.6086) 
(list 2240.4687 869.6189) 
(list 2240.4759 869.6292) 
(list 2240.4812 869.6394) 
(list 2240.4846 869.6497) 
(list 2240.4859 869.66) 
(list 2240.4859 869.66)))
(apply 'command (append '("pline") coords '("c")))
(setq tap7 (ssadd (entlast) tap7))
(command "_mirror" (entlast) "" "2240,900" "2240,901" "No")
(setq tap7 (ssadd (entlast) tap7))
(setq coords (list 
(list 2241.096 869.29) 
(list 2240.4859 869.29) 
(list 2240.4859 869.3003) 
(list 2240.4859 869.3106) 
(list 2240.4859 869.3208) 
(list 2240.4859 869.3311) 
(list 2240.4859 869.3414) 
(list 2240.4859 869.3517) 
(list 2240.4859 869.3619) 
(list 2240.4859 869.3722) 
(list 2240.4859 869.3825) 
(list 2240.4859 869.3928) 
(list 2240.4859 869.4031) 
(list 2240.4859 869.4133) 
(list 2240.4859 869.4236) 
(list 2240.4859 869.4339) 
(list 2240.4859 869.4442) 
(list 2240.4859 869.4544) 
(list 2240.4859 869.4647) 
(list 2240.4859 869.475) 
(list 2240.4859 869.4853) 
(list 2240.4859 869.4956) 
(list 2240.4859 869.5058) 
(list 2240.4859 869.5161) 
(list 2240.4859 869.5264) 
(list 2240.4859 869.5367) 
(list 2240.4859 869.5469) 
(list 2240.4859 869.5572) 
(list 2240.4859 869.5675) 
(list 2240.4859 869.5778) 
(list 2240.4859 869.5881) 
(list 2240.4859 869.5983) 
(list 2240.4859 869.6086) 
(list 2240.4859 869.6189) 
(list 2240.4859 869.6292) 
(list 2240.4859 869.6394) 
(list 2240.4859 869.6497) 
(list 2240.4859 869.66) 
(list 2241.096 869.66)))
(apply 'command (append '("pline") coords '("c")))
(setq tap7 (ssadd (entlast) tap7))
(command "_mirror" (entlast) "" "2240,900" "2240,901" "No")
(setq tap7 (ssadd (entlast) tap7))
(setq coords (list 
(list 2240 869.66) 
(list 2240.135 869.66) 
(list 2240.135 869.6703) 
(list 2240.135 869.6806) 
(list 2240.135 869.6908) 
(list 2240.135 869.7011) 
(list 2240.135 869.7114) 
(list 2240.135 869.7217) 
(list 2240.135 869.7319) 
(list 2240.135 869.7422) 
(list 2240.135 869.7525) 
(list 2240.135 869.7628) 
(list 2240.135 869.7731) 
(list 2240.135 869.7833) 
(list 2240.135 869.7936) 
(list 2240.135 869.8039) 
(list 2240.135 869.8142) 
(list 2240.135 869.8244) 
(list 2240.135 869.8347) 
(list 2240.135 869.845) 
(list 2240.135 869.8553) 
(list 2240.135 869.8656) 
(list 2240.135 869.8758) 
(list 2240.135 869.8861) 
(list 2240.135 869.8964) 
(list 2240.135 869.9067) 
(list 2240.135 869.9169) 
(list 2240.135 869.9272) 
(list 2240.135 869.9375) 
(list 2240.135 869.9478) 
(list 2240.135 869.9581) 
(list 2240.135 869.9683) 
(list 2240.135 869.9786) 
(list 2240.135 869.9889) 
(list 2240.135 869.9992) 
(list 2240.135 870.0094) 
(list 2240.135 870.0197) 
(list 2240.135 870.03) 
(list 2240 870.03)))
(apply 'command (append '("pline") coords '("c")))
(setq tap7 (ssadd (entlast) tap7))
(command "_mirror" (entlast) "" "2240,900" "2240,901" "No")
(setq tap7 (ssadd (entlast) tap7))
(setq coords (list 
(list 2240.4948 869.66) 
(list 2240.4859 869.66) 
(list 2240.4851 869.6703) 
(list 2240.4822 869.6806) 
(list 2240.4771 869.6908) 
(list 2240.4702 869.7011) 
(list 2240.4616 869.7114) 
(list 2240.4515 869.7217) 
(list 2240.4402 869.7319) 
(list 2240.4281 869.7422) 
(list 2240.4156 869.7525) 
(list 2240.4029 869.7628) 
(list 2240.3906 869.7731) 
(list 2240.3789 869.7833) 
(list 2240.3683 869.7936) 
(list 2240.359 869.8039) 
(list 2240.3514 869.8142) 
(list 2240.3457 869.8244) 
(list 2240.3421 869.8347) 
(list 2240.3408 869.845) 
(list 2240.3417 869.8553) 
(list 2240.3448 869.8656) 
(list 2240.3502 869.8758) 
(list 2240.3575 869.8861) 
(list 2240.3667 869.8964) 
(list 2240.3774 869.9067) 
(list 2240.3894 869.9169) 
(list 2240.4023 869.9272) 
(list 2240.4156 869.9375) 
(list 2240.429 869.9478) 
(list 2240.4421 869.9581) 
(list 2240.4545 869.9683) 
(list 2240.4657 869.9786) 
(list 2240.4755 869.9889) 
(list 2240.4835 869.9992) 
(list 2240.4896 870.0094) 
(list 2240.4934 870.0197) 
(list 2240.4948 870.03) 
(list 2240.4948 870.03)))
(apply 'command (append '("pline") coords '("c")))
(setq tap7 (ssadd (entlast) tap7))
(command "_mirror" (entlast) "" "2240,900" "2240,901" "No")
(setq tap7 (ssadd (entlast) tap7))
(setq coords (list 
(list 2241.096 869.66) 
(list 2240.4948 869.66) 
(list 2240.4948 869.6703) 
(list 2240.4948 869.6806) 
(list 2240.4948 869.6908) 
(list 2240.4948 869.7011) 
(list 2240.4948 869.7114) 
(list 2240.4948 869.7217) 
(list 2240.4948 869.7319) 
(list 2240.4948 869.7422) 
(list 2240.4948 869.7525) 
(list 2240.4948 869.7628) 
(list 2240.4948 869.7731) 
(list 2240.4948 869.7833) 
(list 2240.4948 869.7936) 
(list 2240.4948 869.8039) 
(list 2240.4948 869.8142) 
(list 2240.4948 869.8244) 
(list 2240.4948 869.8347) 
(list 2240.4948 869.845) 
(list 2240.4948 869.8553) 
(list 2240.4948 869.8656) 
(list 2240.4948 869.8758) 
(list 2240.4948 869.8861) 
(list 2240.4948 869.8964) 
(list 2240.4948 869.9067) 
(list 2240.4948 869.9169) 
(list 2240.4948 869.9272) 
(list 2240.4948 869.9375) 
(list 2240.4948 869.9478) 
(list 2240.4948 869.9581) 
(list 2240.4948 869.9683) 
(list 2240.4948 869.9786) 
(list 2240.4948 869.9889) 
(list 2240.4948 869.9992) 
(list 2240.4948 870.0094) 
(list 2240.4948 870.0197) 
(list 2240.4948 870.03) 
(list 2241.096 870.03)))
(apply 'command (append '("pline") coords '("c")))
(setq tap7 (ssadd (entlast) tap7))
(command "_mirror" (entlast) "" "2240,900" "2240,901" "No")
(setq tap7 (ssadd (entlast) tap7))
(setq coords (list 
(list 2240 870.03) 
(list 2240.135 870.03) 
(list 2240.135 870.0403) 
(list 2240.135 870.0506) 
(list 2240.135 870.0608) 
(list 2240.135 870.0711) 
(list 2240.135 870.0814) 
(list 2240.135 870.0917) 
(list 2240.135 870.1019) 
(list 2240.135 870.1122) 
(list 2240.135 870.1225) 
(list 2240.135 870.1328) 
(list 2240.135 870.1431) 
(list 2240.135 870.1533) 
(list 2240.135 870.1636) 
(list 2240.135 870.1739) 
(list 2240.135 870.1842) 
(list 2240.135 870.1944) 
(list 2240.135 870.2047) 
(list 2240.135 870.215) 
(list 2240.135 870.2253) 
(list 2240.135 870.2356) 
(list 2240.135 870.2458) 
(list 2240.135 870.2561) 
(list 2240.135 870.2664) 
(list 2240.135 870.2767) 
(list 2240.135 870.2869) 
(list 2240.135 870.2972) 
(list 2240.135 870.3075) 
(list 2240.135 870.3178) 
(list 2240.135 870.3281) 
(list 2240.135 870.3383) 
(list 2240.135 870.3486) 
(list 2240.135 870.3589) 
(list 2240.135 870.3692) 
(list 2240.135 870.3794) 
(list 2240.135 870.3897) 
(list 2240.135 870.4) 
(list 2240 870.4)))
(apply 'command (append '("pline") coords '("c")))
(setq tap7 (ssadd (entlast) tap7))
(command "_mirror" (entlast) "" "2240,900" "2240,901" "No")
(setq tap7 (ssadd (entlast) tap7))
(setq coords (list 
(list 2240.5037 870.03) 
(list 2240.4948 870.03) 
(list 2240.4938 870.0403) 
(list 2240.4905 870.0506) 
(list 2240.4848 870.0608) 
(list 2240.477 870.0711) 
(list 2240.4673 870.0814) 
(list 2240.4559 870.0917) 
(list 2240.4433 870.1019) 
(list 2240.4297 870.1122) 
(list 2240.4156 870.1225) 
(list 2240.4014 870.1328) 
(list 2240.3876 870.1431) 
(list 2240.3746 870.1533) 
(list 2240.3627 870.1636) 
(list 2240.3523 870.1739) 
(list 2240.3439 870.1842) 
(list 2240.3375 870.1944) 
(list 2240.3335 870.2047) 
(list 2240.332 870.215) 
(list 2240.3331 870.2253) 
(list 2240.3366 870.2356) 
(list 2240.3426 870.2458) 
(list 2240.3508 870.2561) 
(list 2240.3611 870.2664) 
(list 2240.3731 870.2767) 
(list 2240.3865 870.2869) 
(list 2240.4008 870.2972) 
(list 2240.4156 870.3075) 
(list 2240.4306 870.3178) 
(list 2240.4452 870.3281) 
(list 2240.4589 870.3383) 
(list 2240.4714 870.3486) 
(list 2240.4823 870.3589) 
(list 2240.4912 870.3692) 
(list 2240.4979 870.3794) 
(list 2240.5021 870.3897) 
(list 2240.5037 870.4) 
(list 2240.5037 870.4)))
(apply 'command (append '("pline") coords '("c")))
(setq tap7 (ssadd (entlast) tap7))
(command "_mirror" (entlast) "" "2240,900" "2240,901" "No")
(setq tap7 (ssadd (entlast) tap7))
(setq coords (list 
(list 2241.096 870.03) 
(list 2240.5037 870.03) 
(list 2240.5037 870.0403) 
(list 2240.5037 870.0506) 
(list 2240.5037 870.0608) 
(list 2240.5037 870.0711) 
(list 2240.5037 870.0814) 
(list 2240.5037 870.0917) 
(list 2240.5037 870.1019) 
(list 2240.5037 870.1122) 
(list 2240.5037 870.1225) 
(list 2240.5037 870.1328) 
(list 2240.5037 870.1431) 
(list 2240.5037 870.1533) 
(list 2240.5037 870.1636) 
(list 2240.5037 870.1739) 
(list 2240.5037 870.1842) 
(list 2240.5037 870.1944) 
(list 2240.5037 870.2047) 
(list 2240.5037 870.215) 
(list 2240.5037 870.2253) 
(list 2240.5037 870.2356) 
(list 2240.5037 870.2458) 
(list 2240.5037 870.2561) 
(list 2240.5037 870.2664) 
(list 2240.5037 870.2767) 
(list 2240.5037 870.2869) 
(list 2240.5037 870.2972) 
(list 2240.5037 870.3075) 
(list 2240.5037 870.3178) 
(list 2240.5037 870.3281) 
(list 2240.5037 870.3383) 
(list 2240.5037 870.3486) 
(list 2240.5037 870.3589) 
(list 2240.5037 870.3692) 
(list 2240.5037 870.3794) 
(list 2240.5037 870.3897) 
(list 2240.5037 870.4) 
(list 2241.096 870.4)))
(apply 'command (append '("pline") coords '("c")))
(setq tap7 (ssadd (entlast) tap7))
(command "_mirror" (entlast) "" "2240,900" "2240,901" "No")
(setq tap7 (ssadd (entlast) tap7))
(setq coords (list 
(list 2240 870.4) 
(list 2240.135 870.4) 
(list 2240.135 870.4103) 
(list 2240.135 870.4206) 
(list 2240.135 870.4308) 
(list 2240.135 870.4411) 
(list 2240.135 870.4514) 
(list 2240.135 870.4617) 
(list 2240.135 870.4719) 
(list 2240.135 870.4822) 
(list 2240.135 870.4925) 
(list 2240.135 870.5028) 
(list 2240.135 870.5131) 
(list 2240.135 870.5233) 
(list 2240.135 870.5336) 
(list 2240.135 870.5439) 
(list 2240.135 870.5542) 
(list 2240.135 870.5644) 
(list 2240.135 870.5747) 
(list 2240.135 870.585) 
(list 2240.135 870.5953) 
(list 2240.135 870.6056) 
(list 2240.135 870.6158) 
(list 2240.135 870.6261) 
(list 2240.135 870.6364) 
(list 2240.135 870.6467) 
(list 2240.135 870.6569) 
(list 2240.135 870.6672) 
(list 2240.135 870.6775) 
(list 2240.135 870.6878) 
(list 2240.135 870.6981) 
(list 2240.135 870.7083) 
(list 2240.135 870.7186) 
(list 2240.135 870.7289) 
(list 2240.135 870.7392) 
(list 2240.135 870.7494) 
(list 2240.135 870.7597) 
(list 2240.135 870.77) 
(list 2240 870.77)))
(apply 'command (append '("pline") coords '("c")))
(setq tap7 (ssadd (entlast) tap7))
(command "_mirror" (entlast) "" "2240,900" "2240,901" "No")
(setq tap7 (ssadd (entlast) tap7))
(setq coords (list 
(list 2240.5125 870.4) 
(list 2240.5037 870.4) 
(list 2240.5026 870.4103) 
(list 2240.4988 870.4206) 
(list 2240.4925 870.4308) 
(list 2240.4838 870.4411) 
(list 2240.473 870.4514) 
(list 2240.4604 870.4617) 
(list 2240.4464 870.4719) 
(list 2240.4313 870.4822) 
(list 2240.4157 870.4925) 
(list 2240.4 870.5028) 
(list 2240.3847 870.5131) 
(list 2240.3702 870.5233) 
(list 2240.3571 870.5336) 
(list 2240.3457 870.5439) 
(list 2240.3363 870.5542) 
(list 2240.3293 870.5644) 
(list 2240.3249 870.5747) 
(list 2240.3233 870.585) 
(list 2240.3245 870.5953) 
(list 2240.3284 870.6056) 
(list 2240.3351 870.6158) 
(list 2240.3442 870.6261) 
(list 2240.3555 870.6364) 
(list 2240.3688 870.6467) 
(list 2240.3835 870.6569) 
(list 2240.3993 870.6672) 
(list 2240.4157 870.6775) 
(list 2240.4322 870.6878) 
(list 2240.4482 870.6981) 
(list 2240.4634 870.7083) 
(list 2240.4772 870.7186) 
(list 2240.4891 870.7289) 
(list 2240.4989 870.7392) 
(list 2240.5062 870.7494) 
(list 2240.5108 870.7597) 
(list 2240.5125 870.77) 
(list 2240.5125 870.77)))
(apply 'command (append '("pline") coords '("c")))
(setq tap7 (ssadd (entlast) tap7))
(command "_mirror" (entlast) "" "2240,900" "2240,901" "No")
(setq tap7 (ssadd (entlast) tap7))
(setq coords (list 
(list 2241.096 870.4) 
(list 2240.5125 870.4) 
(list 2240.5125 870.4103) 
(list 2240.5125 870.4206) 
(list 2240.5125 870.4308) 
(list 2240.5125 870.4411) 
(list 2240.5125 870.4514) 
(list 2240.5125 870.4617) 
(list 2240.5125 870.4719) 
(list 2240.5125 870.4822) 
(list 2240.5125 870.4925) 
(list 2240.5125 870.5028) 
(list 2240.5125 870.5131) 
(list 2240.5125 870.5233) 
(list 2240.5125 870.5336) 
(list 2240.5125 870.5439) 
(list 2240.5125 870.5542) 
(list 2240.5125 870.5644) 
(list 2240.5125 870.5747) 
(list 2240.5125 870.585) 
(list 2240.5125 870.5953) 
(list 2240.5125 870.6056) 
(list 2240.5125 870.6158) 
(list 2240.5125 870.6261) 
(list 2240.5125 870.6364) 
(list 2240.5125 870.6467) 
(list 2240.5125 870.6569) 
(list 2240.5125 870.6672) 
(list 2240.5125 870.6775) 
(list 2240.5125 870.6878) 
(list 2240.5125 870.6981) 
(list 2240.5125 870.7083) 
(list 2240.5125 870.7186) 
(list 2240.5125 870.7289) 
(list 2240.5125 870.7392) 
(list 2240.5125 870.7494) 
(list 2240.5125 870.7597) 
(list 2240.5125 870.77) 
(list 2241.096 870.77)))
(apply 'command (append '("pline") coords '("c")))
(setq tap7 (ssadd (entlast) tap7))
(command "_mirror" (entlast) "" "2240,900" "2240,901" "No")
(setq tap7 (ssadd (entlast) tap7))
(setq coords (list 
(list 2240 870.77) 
(list 2240.135 870.77) 
(list 2240.135 870.7803) 
(list 2240.135 870.7906) 
(list 2240.135 870.8008) 
(list 2240.135 870.8111) 
(list 2240.135 870.8214) 
(list 2240.135 870.8317) 
(list 2240.135 870.8419) 
(list 2240.135 870.8522) 
(list 2240.135 870.8625) 
(list 2240.135 870.8728) 
(list 2240.135 870.8831) 
(list 2240.135 870.8933) 
(list 2240.135 870.9036) 
(list 2240.135 870.9139) 
(list 2240.135 870.9242) 
(list 2240.135 870.9344) 
(list 2240.135 870.9447) 
(list 2240.135 870.955) 
(list 2240.135 870.9653) 
(list 2240.135 870.9756) 
(list 2240.135 870.9858) 
(list 2240.135 870.9961) 
(list 2240.135 871.0064) 
(list 2240.135 871.0167) 
(list 2240.135 871.0269) 
(list 2240.135 871.0372) 
(list 2240.135 871.0475) 
(list 2240.135 871.0578) 
(list 2240.135 871.0681) 
(list 2240.135 871.0783) 
(list 2240.135 871.0886) 
(list 2240.135 871.0989) 
(list 2240.135 871.1092) 
(list 2240.135 871.1194) 
(list 2240.135 871.1297) 
(list 2240.135 871.14) 
(list 2240 871.14)))
(apply 'command (append '("pline") coords '("c")))
(setq tap7 (ssadd (entlast) tap7))
(command "_mirror" (entlast) "" "2240,900" "2240,901" "No")
(setq tap7 (ssadd (entlast) tap7))
(setq coords (list 
(list 2240.5214 870.77) 
(list 2240.5125 870.77) 
(list 2240.5113 870.7803) 
(list 2240.5072 870.7906) 
(list 2240.5002 870.8008) 
(list 2240.4906 870.8111) 
(list 2240.4788 870.8214) 
(list 2240.4649 870.8317) 
(list 2240.4494 870.8419) 
(list 2240.4329 870.8522) 
(list 2240.4158 870.8625) 
(list 2240.3985 870.8728) 
(list 2240.3817 870.8831) 
(list 2240.3659 870.8933) 
(list 2240.3515 870.9036) 
(list 2240.339 870.9139) 
(list 2240.3288 870.9242) 
(list 2240.3211 870.9344) 
(list 2240.3163 870.9447) 
(list 2240.3146 870.955) 
(list 2240.3159 870.9653) 
(list 2240.3202 870.9756) 
(list 2240.3275 870.9858) 
(list 2240.3375 870.9961) 
(list 2240.3499 871.0064) 
(list 2240.3644 871.0167) 
(list 2240.3806 871.0269) 
(list 2240.3979 871.0372) 
(list 2240.4158 871.0475) 
(list 2240.4338 871.0578) 
(list 2240.4513 871.0681) 
(list 2240.4679 871.0783) 
(list 2240.4829 871.0886) 
(list 2240.4959 871.0989) 
(list 2240.5066 871.1092) 
(list 2240.5146 871.1194) 
(list 2240.5196 871.1297) 
(list 2240.5214 871.14) 
(list 2240.5214 871.14)))
(apply 'command (append '("pline") coords '("c")))
(setq tap7 (ssadd (entlast) tap7))
(command "_mirror" (entlast) "" "2240,900" "2240,901" "No")
(setq tap7 (ssadd (entlast) tap7))
(setq coords (list 
(list 2241.096 870.77) 
(list 2240.5214 870.77) 
(list 2240.5214 870.7803) 
(list 2240.5214 870.7906) 
(list 2240.5214 870.8008) 
(list 2240.5214 870.8111) 
(list 2240.5214 870.8214) 
(list 2240.5214 870.8317) 
(list 2240.5214 870.8419) 
(list 2240.5214 870.8522) 
(list 2240.5214 870.8625) 
(list 2240.5214 870.8728) 
(list 2240.5214 870.8831) 
(list 2240.5214 870.8933) 
(list 2240.5214 870.9036) 
(list 2240.5214 870.9139) 
(list 2240.5214 870.9242) 
(list 2240.5214 870.9344) 
(list 2240.5214 870.9447) 
(list 2240.5214 870.955) 
(list 2240.5214 870.9653) 
(list 2240.5214 870.9756) 
(list 2240.5214 870.9858) 
(list 2240.5214 870.9961) 
(list 2240.5214 871.0064) 
(list 2240.5214 871.0167) 
(list 2240.5214 871.0269) 
(list 2240.5214 871.0372) 
(list 2240.5214 871.0475) 
(list 2240.5214 871.0578) 
(list 2240.5214 871.0681) 
(list 2240.5214 871.0783) 
(list 2240.5214 871.0886) 
(list 2240.5214 871.0989) 
(list 2240.5214 871.1092) 
(list 2240.5214 871.1194) 
(list 2240.5214 871.1297) 
(list 2240.5214 871.14) 
(list 2241.096 871.14)))
(apply 'command (append '("pline") coords '("c")))
(setq tap7 (ssadd (entlast) tap7))
(command "_mirror" (entlast) "" "2240,900" "2240,901" "No")
(setq tap7 (ssadd (entlast) tap7))
(setq coords (list 
(list 2240 871.14) 
(list 2240.135 871.14) 
(list 2240.135 871.1503) 
(list 2240.135 871.1606) 
(list 2240.135 871.1708) 
(list 2240.135 871.1811) 
(list 2240.135 871.1914) 
(list 2240.135 871.2017) 
(list 2240.135 871.2119) 
(list 2240.135 871.2222) 
(list 2240.135 871.2325) 
(list 2240.135 871.2428) 
(list 2240.135 871.2531) 
(list 2240.135 871.2633) 
(list 2240.135 871.2736) 
(list 2240.135 871.2839) 
(list 2240.135 871.2942) 
(list 2240.135 871.3044) 
(list 2240.135 871.3147) 
(list 2240.135 871.325) 
(list 2240.135 871.3353) 
(list 2240.135 871.3456) 
(list 2240.135 871.3558) 
(list 2240.135 871.3661) 
(list 2240.135 871.3764) 
(list 2240.135 871.3867) 
(list 2240.135 871.3969) 
(list 2240.135 871.4072) 
(list 2240.135 871.4175) 
(list 2240.135 871.4278) 
(list 2240.135 871.4381) 
(list 2240.135 871.4483) 
(list 2240.135 871.4586) 
(list 2240.135 871.4689) 
(list 2240.135 871.4792) 
(list 2240.135 871.4894) 
(list 2240.135 871.4997) 
(list 2240.135 871.51) 
(list 2240 871.51)))
(apply 'command (append '("pline") coords '("c")))
(setq tap7 (ssadd (entlast) tap7))
(command "_mirror" (entlast) "" "2240,900" "2240,901" "No")
(setq tap7 (ssadd (entlast) tap7))
(setq coords (list 
(list 2240.5303 871.14) 
(list 2240.5214 871.14) 
(list 2240.52 871.1503) 
(list 2240.5155 871.1606) 
(list 2240.5079 871.1708) 
(list 2240.4975 871.1811) 
(list 2240.4845 871.1914) 
(list 2240.4693 871.2017) 
(list 2240.4525 871.2119) 
(list 2240.4345 871.2222) 
(list 2240.4158 871.2325) 
(list 2240.3971 871.2428) 
(list 2240.3788 871.2531) 
(list 2240.3616 871.2633) 
(list 2240.3459 871.2736) 
(list 2240.3323 871.2839) 
(list 2240.3212 871.2942) 
(list 2240.3129 871.3044) 
(list 2240.3077 871.3147) 
(list 2240.3058 871.325) 
(list 2240.3073 871.3353) 
(list 2240.312 871.3456) 
(list 2240.3199 871.3558) 
(list 2240.3308 871.3661) 
(list 2240.3443 871.3764) 
(list 2240.3601 871.3867) 
(list 2240.3776 871.3969) 
(list 2240.3964 871.4072) 
(list 2240.4158 871.4175) 
(list 2240.4354 871.4278) 
(list 2240.4544 871.4381) 
(list 2240.4723 871.4483) 
(list 2240.4886 871.4586) 
(list 2240.5027 871.4689) 
(list 2240.5143 871.4792) 
(list 2240.5229 871.4894) 
(list 2240.5283 871.4997) 
(list 2240.5303 871.51) 
(list 2240.5303 871.51)))
(apply 'command (append '("pline") coords '("c")))
(setq tap7 (ssadd (entlast) tap7))
(command "_mirror" (entlast) "" "2240,900" "2240,901" "No")
(setq tap7 (ssadd (entlast) tap7))
(setq coords (list 
(list 2241.096 871.14) 
(list 2240.5303 871.14) 
(list 2240.5303 871.1503) 
(list 2240.5303 871.1606) 
(list 2240.5303 871.1708) 
(list 2240.5303 871.1811) 
(list 2240.5303 871.1914) 
(list 2240.5303 871.2017) 
(list 2240.5303 871.2119) 
(list 2240.5303 871.2222) 
(list 2240.5303 871.2325) 
(list 2240.5303 871.2428) 
(list 2240.5303 871.2531) 
(list 2240.5303 871.2633) 
(list 2240.5303 871.2736) 
(list 2240.5303 871.2839) 
(list 2240.5303 871.2942) 
(list 2240.5303 871.3044) 
(list 2240.5303 871.3147) 
(list 2240.5303 871.325) 
(list 2240.5303 871.3353) 
(list 2240.5303 871.3456) 
(list 2240.5303 871.3558) 
(list 2240.5303 871.3661) 
(list 2240.5303 871.3764) 
(list 2240.5303 871.3867) 
(list 2240.5303 871.3969) 
(list 2240.5303 871.4072) 
(list 2240.5303 871.4175) 
(list 2240.5303 871.4278) 
(list 2240.5303 871.4381) 
(list 2240.5303 871.4483) 
(list 2240.5303 871.4586) 
(list 2240.5303 871.4689) 
(list 2240.5303 871.4792) 
(list 2240.5303 871.4894) 
(list 2240.5303 871.4997) 
(list 2240.5303 871.51) 
(list 2241.096 871.51)))
(apply 'command (append '("pline") coords '("c")))
(setq tap7 (ssadd (entlast) tap7))
(command "_mirror" (entlast) "" "2240,900" "2240,901" "No")
(setq tap7 (ssadd (entlast) tap7))
(setq coords (list 
(list 2240 871.51) 
(list 2240.135 871.51) 
(list 2240.135 871.5203) 
(list 2240.135 871.5306) 
(list 2240.135 871.5408) 
(list 2240.135 871.5511) 
(list 2240.135 871.5614) 
(list 2240.135 871.5717) 
(list 2240.135 871.5819) 
(list 2240.135 871.5922) 
(list 2240.135 871.6025) 
(list 2240.135 871.6128) 
(list 2240.135 871.6231) 
(list 2240.135 871.6333) 
(list 2240.135 871.6436) 
(list 2240.135 871.6539) 
(list 2240.135 871.6642) 
(list 2240.135 871.6744) 
(list 2240.135 871.6847) 
(list 2240.135 871.695) 
(list 2240.135 871.7053) 
(list 2240.135 871.7156) 
(list 2240.135 871.7258) 
(list 2240.135 871.7361) 
(list 2240.135 871.7464) 
(list 2240.135 871.7567) 
(list 2240.135 871.7669) 
(list 2240.135 871.7772) 
(list 2240.135 871.7875) 
(list 2240.135 871.7978) 
(list 2240.135 871.8081) 
(list 2240.135 871.8183) 
(list 2240.135 871.8286) 
(list 2240.135 871.8389) 
(list 2240.135 871.8492) 
(list 2240.135 871.8594) 
(list 2240.135 871.8697) 
(list 2240.135 871.88) 
(list 2240 871.88)))
(apply 'command (append '("pline") coords '("c")))
(setq tap7 (ssadd (entlast) tap7))
(command "_mirror" (entlast) "" "2240,900" "2240,901" "No")
(setq tap7 (ssadd (entlast) tap7))
(setq coords (list 
(list 2240.5391 871.51) 
(list 2240.5303 871.51) 
(list 2240.5288 871.5203) 
(list 2240.5238 871.5306) 
(list 2240.5156 871.5408) 
(list 2240.5043 871.5511) 
(list 2240.4902 871.5614) 
(list 2240.4738 871.5717) 
(list 2240.4556 871.5819) 
(list 2240.4361 871.5922) 
(list 2240.4159 871.6025) 
(list 2240.3956 871.6128) 
(list 2240.3758 871.6231) 
(list 2240.3572 871.6333) 
(list 2240.3403 871.6436) 
(list 2240.3256 871.6539) 
(list 2240.3136 871.6642) 
(list 2240.3047 871.6744) 
(list 2240.2991 871.6847) 
(list 2240.2971 871.695) 
(list 2240.2987 871.7053) 
(list 2240.3038 871.7156) 
(list 2240.3124 871.7258) 
(list 2240.3242 871.7361) 
(list 2240.3388 871.7464) 
(list 2240.3558 871.7567) 
(list 2240.3747 871.7669) 
(list 2240.3949 871.7772) 
(list 2240.4159 871.7875) 
(list 2240.437 871.7978) 
(list 2240.4575 871.8081) 
(list 2240.4768 871.8183) 
(list 2240.4943 871.8286) 
(list 2240.5096 871.8389) 
(list 2240.522 871.8492) 
(list 2240.5312 871.8594) 
(list 2240.537 871.8697) 
(list 2240.5391 871.88) 
(list 2240.5391 871.88)))
(apply 'command (append '("pline") coords '("c")))
(setq tap7 (ssadd (entlast) tap7))
(command "_mirror" (entlast) "" "2240,900" "2240,901" "No")
(setq tap7 (ssadd (entlast) tap7))
(setq coords (list 
(list 2241.096 871.51) 
(list 2240.5391 871.51) 
(list 2240.5391 871.5203) 
(list 2240.5391 871.5306) 
(list 2240.5391 871.5408) 
(list 2240.5391 871.5511) 
(list 2240.5391 871.5614) 
(list 2240.5391 871.5717) 
(list 2240.5391 871.5819) 
(list 2240.5391 871.5922) 
(list 2240.5391 871.6025) 
(list 2240.5391 871.6128) 
(list 2240.5391 871.6231) 
(list 2240.5391 871.6333) 
(list 2240.5391 871.6436) 
(list 2240.5391 871.6539) 
(list 2240.5391 871.6642) 
(list 2240.5391 871.6744) 
(list 2240.5391 871.6847) 
(list 2240.5391 871.695) 
(list 2240.5391 871.7053) 
(list 2240.5391 871.7156) 
(list 2240.5391 871.7258) 
(list 2240.5391 871.7361) 
(list 2240.5391 871.7464) 
(list 2240.5391 871.7567) 
(list 2240.5391 871.7669) 
(list 2240.5391 871.7772) 
(list 2240.5391 871.7875) 
(list 2240.5391 871.7978) 
(list 2240.5391 871.8081) 
(list 2240.5391 871.8183) 
(list 2240.5391 871.8286) 
(list 2240.5391 871.8389) 
(list 2240.5391 871.8492) 
(list 2240.5391 871.8594) 
(list 2240.5391 871.8697) 
(list 2240.5391 871.88) 
(list 2241.096 871.88)))
(apply 'command (append '("pline") coords '("c")))
(setq tap7 (ssadd (entlast) tap7))
(command "_mirror" (entlast) "" "2240,900" "2240,901" "No")
(setq tap7 (ssadd (entlast) tap7))
(setq coords (list 
(list 2240 871.88) 
(list 2240.135 871.88) 
(list 2240.135 871.8903) 
(list 2240.135 871.9006) 
(list 2240.135 871.9108) 
(list 2240.135 871.9211) 
(list 2240.135 871.9314) 
(list 2240.135 871.9417) 
(list 2240.135 871.9519) 
(list 2240.135 871.9622) 
(list 2240.135 871.9725) 
(list 2240.135 871.9828) 
(list 2240.135 871.9931) 
(list 2240.135 872.0033) 
(list 2240.135 872.0136) 
(list 2240.135 872.0239) 
(list 2240.135 872.0342) 
(list 2240.135 872.0444) 
(list 2240.135 872.0547) 
(list 2240.135 872.065) 
(list 2240.135 872.0753) 
(list 2240.135 872.0856) 
(list 2240.135 872.0958) 
(list 2240.135 872.1061) 
(list 2240.135 872.1164) 
(list 2240.135 872.1267) 
(list 2240.135 872.1369) 
(list 2240.135 872.1472) 
(list 2240.135 872.1575) 
(list 2240.135 872.1678) 
(list 2240.135 872.1781) 
(list 2240.135 872.1883) 
(list 2240.135 872.1986) 
(list 2240.135 872.2089) 
(list 2240.135 872.2192) 
(list 2240.135 872.2294) 
(list 2240.135 872.2397) 
(list 2240.135 872.25) 
(list 2240 872.25)))
(apply 'command (append '("pline") coords '("c")))
(setq tap7 (ssadd (entlast) tap7))
(command "_mirror" (entlast) "" "2240,900" "2240,901" "No")
(setq tap7 (ssadd (entlast) tap7))
(setq coords (list 
(list 2240.548 871.88) 
(list 2240.5391 871.88) 
(list 2240.5375 871.8903) 
(list 2240.5322 871.9006) 
(list 2240.5233 871.9108) 
(list 2240.5111 871.9211) 
(list 2240.4959 871.9314) 
(list 2240.4783 871.9417) 
(list 2240.4587 871.9519) 
(list 2240.4377 871.9622) 
(list 2240.416 871.9725) 
(list 2240.3941 871.9828) 
(list 2240.3729 871.9931) 
(list 2240.3529 872.0033) 
(list 2240.3347 872.0136) 
(list 2240.319 872.0239) 
(list 2240.3061 872.0342) 
(list 2240.2965 872.0444) 
(list 2240.2905 872.0547) 
(list 2240.2884 872.065) 
(list 2240.2901 872.0753) 
(list 2240.2956 872.0856) 
(list 2240.3048 872.0958) 
(list 2240.3175 872.1061) 
(list 2240.3332 872.1164) 
(list 2240.3514 872.1267) 
(list 2240.3718 872.1369) 
(list 2240.3935 872.1472) 
(list 2240.416 872.1575) 
(list 2240.4386 872.1678) 
(list 2240.4605 872.1781) 
(list 2240.4813 872.1883) 
(list 2240.5001 872.1986) 
(list 2240.5164 872.2089) 
(list 2240.5297 872.2192) 
(list 2240.5396 872.2294) 
(list 2240.5458 872.2397) 
(list 2240.548 872.25) 
(list 2240.548 872.25)))
(apply 'command (append '("pline") coords '("c")))
(setq tap7 (ssadd (entlast) tap7))
(command "_mirror" (entlast) "" "2240,900" "2240,901" "No")
(setq tap7 (ssadd (entlast) tap7))
(setq coords (list 
(list 2241.096 871.88) 
(list 2240.548 871.88) 
(list 2240.548 871.8903) 
(list 2240.548 871.9006) 
(list 2240.548 871.9108) 
(list 2240.548 871.9211) 
(list 2240.548 871.9314) 
(list 2240.548 871.9417) 
(list 2240.548 871.9519) 
(list 2240.548 871.9622) 
(list 2240.548 871.9725) 
(list 2240.548 871.9828) 
(list 2240.548 871.9931) 
(list 2240.548 872.0033) 
(list 2240.548 872.0136) 
(list 2240.548 872.0239) 
(list 2240.548 872.0342) 
(list 2240.548 872.0444) 
(list 2240.548 872.0547) 
(list 2240.548 872.065) 
(list 2240.548 872.0753) 
(list 2240.548 872.0856) 
(list 2240.548 872.0958) 
(list 2240.548 872.1061) 
(list 2240.548 872.1164) 
(list 2240.548 872.1267) 
(list 2240.548 872.1369) 
(list 2240.548 872.1472) 
(list 2240.548 872.1575) 
(list 2240.548 872.1678) 
(list 2240.548 872.1781) 
(list 2240.548 872.1883) 
(list 2240.548 872.1986) 
(list 2240.548 872.2089) 
(list 2240.548 872.2192) 
(list 2240.548 872.2294) 
(list 2240.548 872.2397) 
(list 2240.548 872.25) 
(list 2241.096 872.25)))
(apply 'command (append '("pline") coords '("c")))
(setq tap7 (ssadd (entlast) tap7))
(command "_mirror" (entlast) "" "2240,900" "2240,901" "No")
(setq tap7 (ssadd (entlast) tap7))
(command "_block" "blktap7" "2240,900" tap7 "")
(command "_insert" "blktap7" "2240,900" "1" "1" "0")
(command "_insert" "blktap7" "2240,900" "1" "1" "180")
(setq uc7 nil)
(setq uc7 (ssadd))
(setq coords (list 
(list 0 -0.185) 
(list 0.135 -0.185) 
(list 0.135 -0.17472) 
(list 0.135 -0.16444) 
(list 0.135 -0.15417) 
(list 0.135 -0.14389) 
(list 0.135 -0.13361) 
(list 0.135 -0.12333) 
(list 0.135 -0.11306) 
(list 0.135 -0.10278) 
(list 0.135 -0.0925) 
(list 0.135 -0.082222) 
(list 0.135 -0.071944) 
(list 0.135 -0.061667) 
(list 0.135 -0.051389) 
(list 0.135 -0.041111) 
(list 0.135 -0.030833) 
(list 0.135 -0.020556) 
(list 0.135 -0.010278) 
(list 0.135 0) 
(list 0.135 0.010278) 
(list 0.135 0.020556) 
(list 0.135 0.030833) 
(list 0.135 0.041111) 
(list 0.135 0.051389) 
(list 0.135 0.061667) 
(list 0.135 0.071944) 
(list 0.135 0.082222) 
(list 0.135 0.0925) 
(list 0.135 0.10278) 
(list 0.135 0.11306) 
(list 0.135 0.12333) 
(list 0.135 0.13361) 
(list 0.135 0.14389) 
(list 0.135 0.15417) 
(list 0.135 0.16444) 
(list 0.135 0.17472) 
(list 0.135 0.185) 
(list 0 0.185)))
(apply 'command (append '("pline") coords '("c")))
(setq uc7 (ssadd (entlast) uc7))
(setq coords (list 
(list 1.096 -0.185) 
(list 0.548 -0.185) 
(list 0.546 -0.17472) 
(list 0.54004 -0.16444) 
(list 0.53031 -0.15417) 
(list 0.51712 -0.14389) 
(list 0.50085 -0.13361) 
(list 0.482 -0.12333) 
(list 0.46115 -0.11306) 
(list 0.43892 -0.10278) 
(list 0.416 -0.0925) 
(list 0.39308 -0.082222) 
(list 0.37085 -0.071944) 
(list 0.35 -0.061667) 
(list 0.33115 -0.051389) 
(list 0.31488 -0.041111) 
(list 0.30168 -0.030833) 
(list 0.29196 -0.020556) 
(list 0.28601 -0.010278) 
(list 0.284 0) 
(list 0.28601 0.010278) 
(list 0.29196 0.020556) 
(list 0.30168 0.030833) 
(list 0.31488 0.041111) 
(list 0.33115 0.051389) 
(list 0.35 0.061667) 
(list 0.37085 0.071944) 
(list 0.39308 0.082222) 
(list 0.416 0.0925) 
(list 0.43892 0.10278) 
(list 0.46115 0.11306) 
(list 0.482 0.12333) 
(list 0.50085 0.13361) 
(list 0.51712 0.14389) 
(list 0.53031 0.15417) 
(list 0.54004 0.16444) 
(list 0.546 0.17472) 
(list 0.548 0.185) 
(list 1.096 0.185)))
(apply 'command (append '("pline") coords '("c")))
(setq uc7 (ssadd (entlast) uc7))
(command "_block" "blkuc7" "0,0.185" uc7 "")
(command "_insert" "blkuc7" "2240,872.62" "1" "1" "0")
(command "_insert" "blkuc7" "2240,872.25" "1" "1" "180")
(command "_insert" "blkuc7" "2240,872.99" "1" "1" "0")
(command "_insert" "blkuc7" "2240,872.62" "1" "1" "180")
(command "_insert" "blkuc7" "2240,873.36" "1" "1" "0")
(command "_insert" "blkuc7" "2240,872.99" "1" "1" "180")
(command "_insert" "blkuc7" "2240,873.73" "1" "1" "0")
(command "_insert" "blkuc7" "2240,873.36" "1" "1" "180")
(command "_insert" "blkuc7" "2240,874.1" "1" "1" "0")
(command "_insert" "blkuc7" "2240,873.73" "1" "1" "180")
(command "_insert" "blkuc7" "2240,874.47" "1" "1" "0")
(command "_insert" "blkuc7" "2240,874.1" "1" "1" "180")
(command "_insert" "blkuc7" "2240,874.84" "1" "1" "0")
(command "_insert" "blkuc7" "2240,874.47" "1" "1" "180")
(command "_insert" "blkuc7" "2240,875.21" "1" "1" "0")
(command "_insert" "blkuc7" "2240,874.84" "1" "1" "180")
(command "_insert" "blkuc7" "2240,875.58" "1" "1" "0")
(command "_insert" "blkuc7" "2240,875.21" "1" "1" "180")
(command "_insert" "blkuc7" "2240,875.95" "1" "1" "0")
(command "_insert" "blkuc7" "2240,875.58" "1" "1" "180")
(command "_insert" "blkuc7" "2240,876.32" "1" "1" "0")
(command "_insert" "blkuc7" "2240,875.95" "1" "1" "180")
(command "_insert" "blkuc7" "2240,876.69" "1" "1" "0")
(command "_insert" "blkuc7" "2240,876.32" "1" "1" "180")
(command "_insert" "blkuc7" "2240,877.06" "1" "1" "0")
(command "_insert" "blkuc7" "2240,876.69" "1" "1" "180")
(command "_insert" "blkuc7" "2240,877.43" "1" "1" "0")
(command "_insert" "blkuc7" "2240,877.06" "1" "1" "180")
(command "_insert" "blkuc7" "2240,877.8" "1" "1" "0")
(command "_insert" "blkuc7" "2240,877.43" "1" "1" "180")
(command "_insert" "blkuc7" "2240,878.17" "1" "1" "0")
(command "_insert" "blkuc7" "2240,877.8" "1" "1" "180")
(command "_insert" "blkuc7" "2240,878.54" "1" "1" "0")
(command "_insert" "blkuc7" "2240,878.17" "1" "1" "180")
(command "_insert" "blkuc7" "2240,878.91" "1" "1" "0")
(command "_insert" "blkuc7" "2240,878.54" "1" "1" "180")
(command "_insert" "blkuc7" "2240,879.28" "1" "1" "0")
(command "_insert" "blkuc7" "2240,878.91" "1" "1" "180")
(command "_insert" "blkuc7" "2240,879.65" "1" "1" "0")
(command "_insert" "blkuc7" "2240,879.28" "1" "1" "180")
(command "_insert" "blkuc7" "2240,880.02" "1" "1" "0")
(command "_insert" "blkuc7" "2240,879.65" "1" "1" "180")
(command "_insert" "blkuc7" "2240,880.39" "1" "1" "0")
(command "_insert" "blkuc7" "2240,880.02" "1" "1" "180")
(command "_insert" "blkuc7" "2240,880.76" "1" "1" "0")
(command "_insert" "blkuc7" "2240,880.39" "1" "1" "180")
(command "_insert" "blkuc7" "2240,881.13" "1" "1" "0")
(command "_insert" "blkuc7" "2240,880.76" "1" "1" "180")
(command "_insert" "blkuc7" "2240,881.5" "1" "1" "0")
(command "_insert" "blkuc7" "2240,881.13" "1" "1" "180")
(command "_insert" "blkuc7" "2240,881.87" "1" "1" "0")
(command "_insert" "blkuc7" "2240,881.5" "1" "1" "180")
(command "_insert" "blkuc7" "2240,882.24" "1" "1" "0")
(command "_insert" "blkuc7" "2240,881.87" "1" "1" "180")
(command "_insert" "blkuc7" "2240,882.61" "1" "1" "0")
(command "_insert" "blkuc7" "2240,882.24" "1" "1" "180")
(command "_insert" "blkuc7" "2240,882.98" "1" "1" "0")
(command "_insert" "blkuc7" "2240,882.61" "1" "1" "180")
(command "_insert" "blkuc7" "2240,883.35" "1" "1" "0")
(command "_insert" "blkuc7" "2240,882.98" "1" "1" "180")
(command "_insert" "blkuc7" "2240,883.72" "1" "1" "0")
(command "_insert" "blkuc7" "2240,883.35" "1" "1" "180")
(command "_insert" "blkuc7" "2240,884.09" "1" "1" "0")
(command "_insert" "blkuc7" "2240,883.72" "1" "1" "180")
(command "_insert" "blkuc7" "2240,884.46" "1" "1" "0")
(command "_insert" "blkuc7" "2240,884.09" "1" "1" "180")
(command "_insert" "blkuc7" "2240,884.83" "1" "1" "0")
(command "_insert" "blkuc7" "2240,884.46" "1" "1" "180")
(command "_insert" "blkuc7" "2240,885.2" "1" "1" "0")
(command "_insert" "blkuc7" "2240,884.83" "1" "1" "180")
(command "_insert" "blkuc7" "2240,885.57" "1" "1" "0")
(command "_insert" "blkuc7" "2240,885.2" "1" "1" "180")
(command "_insert" "blkuc7" "2240,885.94" "1" "1" "0")
(command "_insert" "blkuc7" "2240,885.57" "1" "1" "180")
(command "_insert" "blkuc7" "2240,886.31" "1" "1" "0")
(command "_insert" "blkuc7" "2240,885.94" "1" "1" "180")
(command "_insert" "blkuc7" "2240,886.68" "1" "1" "0")
(command "_insert" "blkuc7" "2240,886.31" "1" "1" "180")
(command "_insert" "blkuc7" "2240,887.05" "1" "1" "0")
(command "_insert" "blkuc7" "2240,886.68" "1" "1" "180")
(command "_insert" "blkuc7" "2240,887.42" "1" "1" "0")
(command "_insert" "blkuc7" "2240,887.05" "1" "1" "180")
(command "_insert" "blkuc7" "2240,887.79" "1" "1" "0")
(command "_insert" "blkuc7" "2240,887.42" "1" "1" "180")
(command "_insert" "blkuc7" "2240,888.16" "1" "1" "0")
(command "_insert" "blkuc7" "2240,887.79" "1" "1" "180")
(command "_insert" "blkuc7" "2240,888.53" "1" "1" "0")
(command "_insert" "blkuc7" "2240,888.16" "1" "1" "180")
(command "_insert" "blkuc7" "2240,888.9" "1" "1" "0")
(command "_insert" "blkuc7" "2240,888.53" "1" "1" "180")
(command "_insert" "blkuc7" "2240,889.27" "1" "1" "0")
(command "_insert" "blkuc7" "2240,888.9" "1" "1" "180")
(command "_insert" "blkuc7" "2240,889.64" "1" "1" "0")
(command "_insert" "blkuc7" "2240,889.27" "1" "1" "180")
(command "_insert" "blkuc7" "2240,890.01" "1" "1" "0")
(command "_insert" "blkuc7" "2240,889.64" "1" "1" "180")
(command "_insert" "blkuc7" "2240,890.38" "1" "1" "0")
(command "_insert" "blkuc7" "2240,890.01" "1" "1" "180")
(command "_insert" "blkuc7" "2240,890.75" "1" "1" "0")
(command "_insert" "blkuc7" "2240,890.38" "1" "1" "180")
(command "_insert" "blkuc7" "2240,891.12" "1" "1" "0")
(command "_insert" "blkuc7" "2240,890.75" "1" "1" "180")
(command "_insert" "blkuc7" "2240,891.49" "1" "1" "0")
(command "_insert" "blkuc7" "2240,891.12" "1" "1" "180")
(command "_insert" "blkuc7" "2240,891.86" "1" "1" "0")
(command "_insert" "blkuc7" "2240,891.49" "1" "1" "180")
(command "_insert" "blkuc7" "2240,892.23" "1" "1" "0")
(command "_insert" "blkuc7" "2240,891.86" "1" "1" "180")
(command "_insert" "blkuc7" "2240,892.6" "1" "1" "0")
(command "_insert" "blkuc7" "2240,892.23" "1" "1" "180")
(command "_insert" "blkuc7" "2240,892.97" "1" "1" "0")
(command "_insert" "blkuc7" "2240,892.6" "1" "1" "180")
(command "_insert" "blkuc7" "2240,893.34" "1" "1" "0")
(command "_insert" "blkuc7" "2240,892.97" "1" "1" "180")
(command "_insert" "blkuc7" "2240,893.71" "1" "1" "0")
(command "_insert" "blkuc7" "2240,893.34" "1" "1" "180")
(command "_insert" "blkuc7" "2240,894.08" "1" "1" "0")
(command "_insert" "blkuc7" "2240,893.71" "1" "1" "180")
(command "_insert" "blkuc7" "2240,894.45" "1" "1" "0")
(command "_insert" "blkuc7" "2240,894.08" "1" "1" "180")
(command "_insert" "blkuc7" "2240,894.82" "1" "1" "0")
(command "_insert" "blkuc7" "2240,894.45" "1" "1" "180")
(command "_insert" "blkuc7" "2240,895.19" "1" "1" "0")
(command "_insert" "blkuc7" "2240,894.82" "1" "1" "180")
(command "_insert" "blkuc7" "2240,895.56" "1" "1" "0")
(command "_insert" "blkuc7" "2240,895.19" "1" "1" "180")
(command "_insert" "blkuc7" "2240,895.93" "1" "1" "0")
(command "_insert" "blkuc7" "2240,895.56" "1" "1" "180")
(command "_insert" "blkuc7" "2240,896.3" "1" "1" "0")
(command "_insert" "blkuc7" "2240,895.93" "1" "1" "180")
(command "_insert" "blkuc7" "2240,896.67" "1" "1" "0")
(command "_insert" "blkuc7" "2240,896.3" "1" "1" "180")
(command "_insert" "blkuc7" "2240,897.04" "1" "1" "0")
(command "_insert" "blkuc7" "2240,896.67" "1" "1" "180")
(command "_insert" "blkuc7" "2240,897.41" "1" "1" "0")
(command "_insert" "blkuc7" "2240,897.04" "1" "1" "180")
(command "_insert" "blkuc7" "2240,897.78" "1" "1" "0")
(command "_insert" "blkuc7" "2240,897.41" "1" "1" "180")
(command "_insert" "blkuc7" "2240,898.15" "1" "1" "0")
(command "_insert" "blkuc7" "2240,897.78" "1" "1" "180")
(command "_insert" "blkuc7" "2240,898.52" "1" "1" "0")
(command "_insert" "blkuc7" "2240,898.15" "1" "1" "180")
(command "_insert" "blkuc7" "2240,898.89" "1" "1" "0")
(command "_insert" "blkuc7" "2240,898.52" "1" "1" "180")
(command "_insert" "blkuc7" "2240,899.26" "1" "1" "0")
(command "_insert" "blkuc7" "2240,898.89" "1" "1" "180")
(command "_insert" "blkuc7" "2240,899.63" "1" "1" "0")
(command "_insert" "blkuc7" "2240,899.26" "1" "1" "180")
(command "_insert" "blkuc7" "2240,900" "1" "1" "0")
(command "_insert" "blkuc7" "2240,899.63" "1" "1" "180")
(command "_insert" "blkuc7" "2240,900.37" "1" "1" "0")
(command "_insert" "blkuc7" "2240,900" "1" "1" "180")
(command "_insert" "blkuc7" "2240,900.74" "1" "1" "0")
(command "_insert" "blkuc7" "2240,900.37" "1" "1" "180")
(command "_insert" "blkuc7" "2240,901.11" "1" "1" "0")
(command "_insert" "blkuc7" "2240,900.74" "1" "1" "180")
(command "_insert" "blkuc7" "2240,901.48" "1" "1" "0")
(command "_insert" "blkuc7" "2240,901.11" "1" "1" "180")
(command "_insert" "blkuc7" "2240,901.85" "1" "1" "0")
(command "_insert" "blkuc7" "2240,901.48" "1" "1" "180")
(command "_insert" "blkuc7" "2240,902.22" "1" "1" "0")
(command "_insert" "blkuc7" "2240,901.85" "1" "1" "180")
(command "_insert" "blkuc7" "2240,902.59" "1" "1" "0")
(command "_insert" "blkuc7" "2240,902.22" "1" "1" "180")
(command "_insert" "blkuc7" "2240,902.96" "1" "1" "0")
(command "_insert" "blkuc7" "2240,902.59" "1" "1" "180")
(command "_insert" "blkuc7" "2240,903.33" "1" "1" "0")
(command "_insert" "blkuc7" "2240,902.96" "1" "1" "180")
(command "_insert" "blkuc7" "2240,903.7" "1" "1" "0")
(command "_insert" "blkuc7" "2240,903.33" "1" "1" "180")
(command "_insert" "blkuc7" "2240,904.07" "1" "1" "0")
(command "_insert" "blkuc7" "2240,903.7" "1" "1" "180")
(command "_insert" "blkuc7" "2240,904.44" "1" "1" "0")
(command "_insert" "blkuc7" "2240,904.07" "1" "1" "180")
(command "_insert" "blkuc7" "2240,904.81" "1" "1" "0")
(command "_insert" "blkuc7" "2240,904.44" "1" "1" "180")
(command "_insert" "blkuc7" "2240,905.18" "1" "1" "0")
(command "_insert" "blkuc7" "2240,904.81" "1" "1" "180")
(command "_insert" "blkuc7" "2240,905.55" "1" "1" "0")
(command "_insert" "blkuc7" "2240,905.18" "1" "1" "180")
(command "_insert" "blkuc7" "2240,905.92" "1" "1" "0")
(command "_insert" "blkuc7" "2240,905.55" "1" "1" "180")
(command "_insert" "blkuc7" "2240,906.29" "1" "1" "0")
(command "_insert" "blkuc7" "2240,905.92" "1" "1" "180")
(command "_insert" "blkuc7" "2240,906.66" "1" "1" "0")
(command "_insert" "blkuc7" "2240,906.29" "1" "1" "180")
(command "_insert" "blkuc7" "2240,907.03" "1" "1" "0")
(command "_insert" "blkuc7" "2240,906.66" "1" "1" "180")
(command "_insert" "blkuc7" "2240,907.4" "1" "1" "0")
(command "_insert" "blkuc7" "2240,907.03" "1" "1" "180")
(command "_insert" "blkuc7" "2240,907.77" "1" "1" "0")
(command "_insert" "blkuc7" "2240,907.4" "1" "1" "180")
(command "_insert" "blkuc7" "2240,908.14" "1" "1" "0")
(command "_insert" "blkuc7" "2240,907.77" "1" "1" "180")
(command "_insert" "blkuc7" "2240,908.51" "1" "1" "0")
(command "_insert" "blkuc7" "2240,908.14" "1" "1" "180")
(command "_insert" "blkuc7" "2240,908.88" "1" "1" "0")
(command "_insert" "blkuc7" "2240,908.51" "1" "1" "180")
(command "_insert" "blkuc7" "2240,909.25" "1" "1" "0")
(command "_insert" "blkuc7" "2240,908.88" "1" "1" "180")
(command "_insert" "blkuc7" "2240,909.62" "1" "1" "0")
(command "_insert" "blkuc7" "2240,909.25" "1" "1" "180")
(command "_insert" "blkuc7" "2240,909.99" "1" "1" "0")
(command "_insert" "blkuc7" "2240,909.62" "1" "1" "180")
(command "_insert" "blkuc7" "2240,910.36" "1" "1" "0")
(command "_insert" "blkuc7" "2240,909.99" "1" "1" "180")
(command "_insert" "blkuc7" "2240,910.73" "1" "1" "0")
(command "_insert" "blkuc7" "2240,910.36" "1" "1" "180")
(command "_insert" "blkuc7" "2240,911.1" "1" "1" "0")
(command "_insert" "blkuc7" "2240,910.73" "1" "1" "180")
(command "_insert" "blkuc7" "2240,911.47" "1" "1" "0")
(command "_insert" "blkuc7" "2240,911.1" "1" "1" "180")
(command "_insert" "blkuc7" "2240,911.84" "1" "1" "0")
(command "_insert" "blkuc7" "2240,911.47" "1" "1" "180")
(command "_insert" "blkuc7" "2240,912.21" "1" "1" "0")
(command "_insert" "blkuc7" "2240,911.84" "1" "1" "180")
(command "_insert" "blkuc7" "2240,912.58" "1" "1" "0")
(command "_insert" "blkuc7" "2240,912.21" "1" "1" "180")
(command "_insert" "blkuc7" "2240,912.95" "1" "1" "0")
(command "_insert" "blkuc7" "2240,912.58" "1" "1" "180")
(command "_insert" "blkuc7" "2240,913.32" "1" "1" "0")
(command "_insert" "blkuc7" "2240,912.95" "1" "1" "180")
(command "_insert" "blkuc7" "2240,913.69" "1" "1" "0")
(command "_insert" "blkuc7" "2240,913.32" "1" "1" "180")
(command "_insert" "blkuc7" "2240,914.06" "1" "1" "0")
(command "_insert" "blkuc7" "2240,913.69" "1" "1" "180")
(command "_insert" "blkuc7" "2240,914.43" "1" "1" "0")
(command "_insert" "blkuc7" "2240,914.06" "1" "1" "180")
(command "_insert" "blkuc7" "2240,914.8" "1" "1" "0")
(command "_insert" "blkuc7" "2240,914.43" "1" "1" "180")
(command "_insert" "blkuc7" "2240,915.17" "1" "1" "0")
(command "_insert" "blkuc7" "2240,914.8" "1" "1" "180")
(command "_insert" "blkuc7" "2240,915.54" "1" "1" "0")
(command "_insert" "blkuc7" "2240,915.17" "1" "1" "180")
(command "_insert" "blkuc7" "2240,915.91" "1" "1" "0")
(command "_insert" "blkuc7" "2240,915.54" "1" "1" "180")
(command "_insert" "blkuc7" "2240,916.28" "1" "1" "0")
(command "_insert" "blkuc7" "2240,915.91" "1" "1" "180")
(command "_insert" "blkuc7" "2240,916.65" "1" "1" "0")
(command "_insert" "blkuc7" "2240,916.28" "1" "1" "180")
(command "_insert" "blkuc7" "2240,917.02" "1" "1" "0")
(command "_insert" "blkuc7" "2240,916.65" "1" "1" "180")
(command "_insert" "blkuc7" "2240,917.39" "1" "1" "0")
(command "_insert" "blkuc7" "2240,917.02" "1" "1" "180")
(command "_insert" "blkuc7" "2240,917.76" "1" "1" "0")
(command "_insert" "blkuc7" "2240,917.39" "1" "1" "180")
(command "_insert" "blkuc7" "2240,918.13" "1" "1" "0")
(command "_insert" "blkuc7" "2240,917.76" "1" "1" "180")
(command "_insert" "blkuc7" "2240,918.5" "1" "1" "0")
(command "_insert" "blkuc7" "2240,918.13" "1" "1" "180")
(command "_insert" "blkuc7" "2240,918.87" "1" "1" "0")
(command "_insert" "blkuc7" "2240,918.5" "1" "1" "180")
(command "_insert" "blkuc7" "2240,919.24" "1" "1" "0")
(command "_insert" "blkuc7" "2240,918.87" "1" "1" "180")
(command "_insert" "blkuc7" "2240,919.61" "1" "1" "0")
(command "_insert" "blkuc7" "2240,919.24" "1" "1" "180")
(command "_insert" "blkuc7" "2240,919.98" "1" "1" "0")
(command "_insert" "blkuc7" "2240,919.61" "1" "1" "180")
(command "_insert" "blkuc7" "2240,920.35" "1" "1" "0")
(command "_insert" "blkuc7" "2240,919.98" "1" "1" "180")
(command "_insert" "blkuc7" "2240,920.72" "1" "1" "0")
(command "_insert" "blkuc7" "2240,920.35" "1" "1" "180")
(command "_insert" "blkuc7" "2240,921.09" "1" "1" "0")
(command "_insert" "blkuc7" "2240,920.72" "1" "1" "180")
(command "_insert" "blkuc7" "2240,921.46" "1" "1" "0")
(command "_insert" "blkuc7" "2240,921.09" "1" "1" "180")
(command "_insert" "blkuc7" "2240,921.83" "1" "1" "0")
(command "_insert" "blkuc7" "2240,921.46" "1" "1" "180")
(command "_insert" "blkuc7" "2240,922.2" "1" "1" "0")
(command "_insert" "blkuc7" "2240,921.83" "1" "1" "180")
(command "_insert" "blkuc7" "2240,922.57" "1" "1" "0")
(command "_insert" "blkuc7" "2240,922.2" "1" "1" "180")
(command "_insert" "blkuc7" "2240,922.94" "1" "1" "0")
(command "_insert" "blkuc7" "2240,922.57" "1" "1" "180")
(command "_insert" "blkuc7" "2240,923.31" "1" "1" "0")
(command "_insert" "blkuc7" "2240,922.94" "1" "1" "180")
(command "_insert" "blkuc7" "2240,923.68" "1" "1" "0")
(command "_insert" "blkuc7" "2240,923.31" "1" "1" "180")
(command "_insert" "blkuc7" "2240,924.05" "1" "1" "0")
(command "_insert" "blkuc7" "2240,923.68" "1" "1" "180")
(command "_insert" "blkuc7" "2240,924.42" "1" "1" "0")
(command "_insert" "blkuc7" "2240,924.05" "1" "1" "180")
(command "_insert" "blkuc7" "2240,924.79" "1" "1" "0")
(command "_insert" "blkuc7" "2240,924.42" "1" "1" "180")
(command "_insert" "blkuc7" "2240,925.16" "1" "1" "0")
(command "_insert" "blkuc7" "2240,924.79" "1" "1" "180")
(command "_insert" "blkuc7" "2240,925.53" "1" "1" "0")
(command "_insert" "blkuc7" "2240,925.16" "1" "1" "180")
(command "_insert" "blkuc7" "2240,925.9" "1" "1" "0")
(command "_insert" "blkuc7" "2240,925.53" "1" "1" "180")
(command "_insert" "blkuc7" "2240,926.27" "1" "1" "0")
(command "_insert" "blkuc7" "2240,925.9" "1" "1" "180")
(command "_insert" "blkuc7" "2240,926.64" "1" "1" "0")
(command "_insert" "blkuc7" "2240,926.27" "1" "1" "180")
(command "_insert" "blkuc7" "2240,927.01" "1" "1" "0")
(command "_insert" "blkuc7" "2240,926.64" "1" "1" "180")
(command "_insert" "blkuc7" "2240,927.38" "1" "1" "0")
(command "_insert" "blkuc7" "2240,927.01" "1" "1" "180")
(command "_insert" "blkuc7" "2240,927.75" "1" "1" "0")
(command "_insert" "blkuc7" "2240,927.38" "1" "1" "180")
(command "_layer" "set" "phccover" "")
(command "_rectangle" "2238.904,933.3" "2241.096,866.7")
(command "_layer" "set" "nitride" "")
(setq phc7 currobj)
(command "_layer" "set" "cover" "")
(command "_rectangle" "2238.904,836.7" "2241.096,963.3")
(command "_layer" "set" "nitride" "")
(command "_layer" "set" "text" "")
(command "_circle" "2237.954,846.7" "0.075")
(command "_circle" "2237.579,846.7" "0.15")
(command "_circle" "2237.204,846.7" "0.075")
(command "_circle" "2236.829,846.7" "0.15")
(command "_circle" "2237.954,848.7" "0.075")
(command "_circle" "2237.579,848.7" "0.075")
(command "_circle" "2237.204,848.7" "0.15")
(command "_circle" "2236.829,848.7" "0.15")
(command "_circle" "2237.954,850.7" "0.075")
(command "_circle" "2237.579,850.7" "0.15")
(command "_circle" "2237.204,850.7" "0.15")
(command "_circle" "2236.829,850.7" "0.15")
(command "_circle" "2237.954,852.7" "0.075")
(command "_circle" "2237.579,852.7" "0.075")
(command "_circle" "2237.204,852.7" "0.075")
(command "_circle" "2236.829,852.7" "0.075")
(command "_circle" "2236.454,852.7" "0.15")
(command "_circle" "2237.954,854.7" "0.075")
(command "_circle" "2237.579,854.7" "0.15")
(command "_circle" "2237.204,854.7" "0.075")
(command "_circle" "2236.829,854.7" "0.075")
(command "_circle" "2236.454,854.7" "0.15")
(command "_circle" "2237.954,856.7" "0.075")
(command "_circle" "2237.579,856.7" "0.075")
(command "_circle" "2237.204,856.7" "0.15")
(command "_circle" "2236.829,856.7" "0.075")
(command "_circle" "2236.454,856.7" "0.15")
(command "_circle" "2237.954,858.7" "0.075")
(command "_circle" "2237.579,858.7" "0.15")
(command "_circle" "2237.204,858.7" "0.15")
(command "_circle" "2236.829,858.7" "0.075")
(command "_circle" "2236.454,858.7" "0.15")
(command "_circle" "2237.954,860.7" "0.075")
(command "_circle" "2237.579,860.7" "0.075")
(command "_circle" "2237.204,860.7" "0.075")
(command "_circle" "2236.829,860.7" "0.15")
(command "_circle" "2236.454,860.7" "0.15")
(command "_circle" "2237.954,862.7" "0.075")
(command "_circle" "2237.579,862.7" "0.15")
(command "_circle" "2237.204,862.7" "0.075")
(command "_circle" "2236.829,862.7" "0.15")
(command "_circle" "2236.454,862.7" "0.15")
(command "_circle" "2237.954,864.7" "0.075")
(command "_circle" "2237.579,864.7" "0.075")
(command "_circle" "2237.204,864.7" "0.15")
(command "_circle" "2236.829,864.7" "0.15")
(command "_circle" "2236.454,864.7" "0.15")
(command "_circle" "2237.954,866.7" "0.075")
(command "_circle" "2237.579,866.7" "0.15")
(command "_circle" "2237.204,866.7" "0.15")
(command "_circle" "2236.829,866.7" "0.15")
(command "_circle" "2236.454,866.7" "0.15")
(command "_circle" "2237.954,868.7" "0.075")
(command "_circle" "2237.579,868.7" "0.075")
(command "_circle" "2237.204,868.7" "0.075")
(command "_circle" "2236.829,868.7" "0.075")
(command "_circle" "2236.454,868.7" "0.075")
(command "_circle" "2236.079,868.7" "0.15")
(command "_circle" "2237.954,870.7" "0.075")
(command "_circle" "2237.579,870.7" "0.15")
(command "_circle" "2237.204,870.7" "0.075")
(command "_circle" "2236.829,870.7" "0.075")
(command "_circle" "2236.454,870.7" "0.075")
(command "_circle" "2236.079,870.7" "0.15")
(command "_circle" "2237.954,872.7" "0.075")
(command "_circle" "2237.579,872.7" "0.075")
(command "_circle" "2237.204,872.7" "0.15")
(command "_circle" "2236.829,872.7" "0.075")
(command "_circle" "2236.454,872.7" "0.075")
(command "_circle" "2236.079,872.7" "0.15")
(command "_circle" "2237.954,874.7" "0.075")
(command "_circle" "2237.579,874.7" "0.15")
(command "_circle" "2237.204,874.7" "0.15")
(command "_circle" "2236.829,874.7" "0.075")
(command "_circle" "2236.454,874.7" "0.075")
(command "_circle" "2236.079,874.7" "0.15")
(command "_circle" "2237.954,876.7" "0.075")
(command "_circle" "2237.579,876.7" "0.075")
(command "_circle" "2237.204,876.7" "0.075")
(command "_circle" "2236.829,876.7" "0.15")
(command "_circle" "2236.454,876.7" "0.075")
(command "_circle" "2236.079,876.7" "0.15")
(command "_circle" "2237.954,878.7" "0.075")
(command "_circle" "2237.579,878.7" "0.15")
(command "_circle" "2237.204,878.7" "0.075")
(command "_circle" "2236.829,878.7" "0.15")
(command "_circle" "2236.454,878.7" "0.075")
(command "_circle" "2236.079,878.7" "0.15")
(command "_circle" "2237.954,880.7" "0.075")
(command "_circle" "2237.579,880.7" "0.075")
(command "_circle" "2237.204,880.7" "0.15")
(command "_circle" "2236.829,880.7" "0.15")
(command "_circle" "2236.454,880.7" "0.075")
(command "_circle" "2236.079,880.7" "0.15")
(command "_circle" "2237.954,882.7" "0.075")
(command "_circle" "2237.579,882.7" "0.15")
(command "_circle" "2237.204,882.7" "0.15")
(command "_circle" "2236.829,882.7" "0.15")
(command "_circle" "2236.454,882.7" "0.075")
(command "_circle" "2236.079,882.7" "0.15")
(command "_circle" "2237.954,884.7" "0.075")
(command "_circle" "2237.579,884.7" "0.075")
(command "_circle" "2237.204,884.7" "0.075")
(command "_circle" "2236.829,884.7" "0.075")
(command "_circle" "2236.454,884.7" "0.15")
(command "_circle" "2236.079,884.7" "0.15")
(command "_circle" "2237.954,886.7" "0.075")
(command "_circle" "2237.579,886.7" "0.15")
(command "_circle" "2237.204,886.7" "0.075")
(command "_circle" "2236.829,886.7" "0.075")
(command "_circle" "2236.454,886.7" "0.15")
(command "_circle" "2236.079,886.7" "0.15")
(command "_circle" "2237.954,888.7" "0.075")
(command "_circle" "2237.579,888.7" "0.075")
(command "_circle" "2237.204,888.7" "0.15")
(command "_circle" "2236.829,888.7" "0.075")
(command "_circle" "2236.454,888.7" "0.15")
(command "_circle" "2236.079,888.7" "0.15")
(command "_circle" "2237.954,890.7" "0.075")
(command "_circle" "2237.579,890.7" "0.15")
(command "_circle" "2237.204,890.7" "0.15")
(command "_circle" "2236.829,890.7" "0.075")
(command "_circle" "2236.454,890.7" "0.15")
(command "_circle" "2236.079,890.7" "0.15")
(command "_circle" "2237.954,892.7" "0.075")
(command "_circle" "2237.579,892.7" "0.075")
(command "_circle" "2237.204,892.7" "0.075")
(command "_circle" "2236.829,892.7" "0.15")
(command "_circle" "2236.454,892.7" "0.15")
(command "_circle" "2236.079,892.7" "0.15")
(command "_circle" "2237.954,894.7" "0.075")
(command "_circle" "2237.579,894.7" "0.15")
(command "_circle" "2237.204,894.7" "0.075")
(command "_circle" "2236.829,894.7" "0.15")
(command "_circle" "2236.454,894.7" "0.15")
(command "_circle" "2236.079,894.7" "0.15")
(command "_circle" "2237.954,896.7" "0.075")
(command "_circle" "2237.579,896.7" "0.075")
(command "_circle" "2237.204,896.7" "0.15")
(command "_circle" "2236.829,896.7" "0.15")
(command "_circle" "2236.454,896.7" "0.15")
(command "_circle" "2236.079,896.7" "0.15")
(command "_circle" "2237.954,898.7" "0.075")
(command "_circle" "2237.579,898.7" "0.15")
(command "_circle" "2237.204,898.7" "0.15")
(command "_circle" "2236.829,898.7" "0.15")
(command "_circle" "2236.454,898.7" "0.15")
(command "_circle" "2236.079,898.7" "0.15")
(command "_circle" "2237.954,900.7" "0.075")
(command "_circle" "2237.579,900.7" "0.075")
(command "_circle" "2237.204,900.7" "0.075")
(command "_circle" "2236.829,900.7" "0.075")
(command "_circle" "2236.454,900.7" "0.075")
(command "_circle" "2236.079,900.7" "0.075")
(command "_circle" "2235.704,900.7" "0.15")
(command "_circle" "2237.954,902.7" "0.075")
(command "_circle" "2237.579,902.7" "0.15")
(command "_circle" "2237.204,902.7" "0.075")
(command "_circle" "2236.829,902.7" "0.075")
(command "_circle" "2236.454,902.7" "0.075")
(command "_circle" "2236.079,902.7" "0.075")
(command "_circle" "2235.704,902.7" "0.15")
(command "_circle" "2237.954,904.7" "0.075")
(command "_circle" "2237.579,904.7" "0.075")
(command "_circle" "2237.204,904.7" "0.15")
(command "_circle" "2236.829,904.7" "0.075")
(command "_circle" "2236.454,904.7" "0.075")
(command "_circle" "2236.079,904.7" "0.075")
(command "_circle" "2235.704,904.7" "0.15")
(command "_circle" "2237.954,906.7" "0.075")
(command "_circle" "2237.579,906.7" "0.15")
(command "_circle" "2237.204,906.7" "0.15")
(command "_circle" "2236.829,906.7" "0.075")
(command "_circle" "2236.454,906.7" "0.075")
(command "_circle" "2236.079,906.7" "0.075")
(command "_circle" "2235.704,906.7" "0.15")
(command "_circle" "2237.954,908.7" "0.075")
(command "_circle" "2237.579,908.7" "0.075")
(command "_circle" "2237.204,908.7" "0.075")
(command "_circle" "2236.829,908.7" "0.15")
(command "_circle" "2236.454,908.7" "0.075")
(command "_circle" "2236.079,908.7" "0.075")
(command "_circle" "2235.704,908.7" "0.15")
(command "_circle" "2237.954,910.7" "0.075")
(command "_circle" "2237.579,910.7" "0.15")
(command "_circle" "2237.204,910.7" "0.075")
(command "_circle" "2236.829,910.7" "0.15")
(command "_circle" "2236.454,910.7" "0.075")
(command "_circle" "2236.079,910.7" "0.075")
(command "_circle" "2235.704,910.7" "0.15")
(command "_circle" "2237.954,912.7" "0.075")
(command "_circle" "2237.579,912.7" "0.075")
(command "_circle" "2237.204,912.7" "0.15")
(command "_circle" "2236.829,912.7" "0.15")
(command "_circle" "2236.454,912.7" "0.075")
(command "_circle" "2236.079,912.7" "0.075")
(command "_circle" "2235.704,912.7" "0.15")
(command "_circle" "2237.954,914.7" "0.075")
(command "_circle" "2237.579,914.7" "0.15")
(command "_circle" "2237.204,914.7" "0.15")
(command "_circle" "2236.829,914.7" "0.15")
(command "_circle" "2236.454,914.7" "0.075")
(command "_circle" "2236.079,914.7" "0.075")
(command "_circle" "2235.704,914.7" "0.15")
(command "_circle" "2237.954,916.7" "0.075")
(command "_circle" "2237.579,916.7" "0.075")
(command "_circle" "2237.204,916.7" "0.075")
(command "_circle" "2236.829,916.7" "0.075")
(command "_circle" "2236.454,916.7" "0.15")
(command "_circle" "2236.079,916.7" "0.075")
(command "_circle" "2235.704,916.7" "0.15")
(command "_circle" "2237.954,918.7" "0.075")
(command "_circle" "2237.579,918.7" "0.15")
(command "_circle" "2237.204,918.7" "0.075")
(command "_circle" "2236.829,918.7" "0.075")
(command "_circle" "2236.454,918.7" "0.15")
(command "_circle" "2236.079,918.7" "0.075")
(command "_circle" "2235.704,918.7" "0.15")
(command "_circle" "2237.954,920.7" "0.075")
(command "_circle" "2237.579,920.7" "0.075")
(command "_circle" "2237.204,920.7" "0.15")
(command "_circle" "2236.829,920.7" "0.075")
(command "_circle" "2236.454,920.7" "0.15")
(command "_circle" "2236.079,920.7" "0.075")
(command "_circle" "2235.704,920.7" "0.15")
(command "_circle" "2237.954,922.7" "0.075")
(command "_circle" "2237.579,922.7" "0.15")
(command "_circle" "2237.204,922.7" "0.15")
(command "_circle" "2236.829,922.7" "0.075")
(command "_circle" "2236.454,922.7" "0.15")
(command "_circle" "2236.079,922.7" "0.075")
(command "_circle" "2235.704,922.7" "0.15")
(command "_circle" "2237.954,924.7" "0.075")
(command "_circle" "2237.579,924.7" "0.075")
(command "_circle" "2237.204,924.7" "0.075")
(command "_circle" "2236.829,924.7" "0.15")
(command "_circle" "2236.454,924.7" "0.15")
(command "_circle" "2236.079,924.7" "0.075")
(command "_circle" "2235.704,924.7" "0.15")
(command "_circle" "2237.954,926.7" "0.075")
(command "_circle" "2237.579,926.7" "0.15")
(command "_circle" "2237.204,926.7" "0.075")
(command "_circle" "2236.829,926.7" "0.15")
(command "_circle" "2236.454,926.7" "0.15")
(command "_circle" "2236.079,926.7" "0.075")
(command "_circle" "2235.704,926.7" "0.15")
(command "_circle" "2237.954,928.7" "0.075")
(command "_circle" "2237.579,928.7" "0.075")
(command "_circle" "2237.204,928.7" "0.15")
(command "_circle" "2236.829,928.7" "0.15")
(command "_circle" "2236.454,928.7" "0.15")
(command "_circle" "2236.079,928.7" "0.075")
(command "_circle" "2235.704,928.7" "0.15")
(command "_circle" "2237.954,930.7" "0.075")
(command "_circle" "2237.579,930.7" "0.15")
(command "_circle" "2237.204,930.7" "0.15")
(command "_circle" "2236.829,930.7" "0.15")
(command "_circle" "2236.454,930.7" "0.15")
(command "_circle" "2236.079,930.7" "0.075")
(command "_circle" "2235.704,930.7" "0.15")
(command "_circle" "2237.954,932.7" "0.075")
(command "_circle" "2237.579,932.7" "0.075")
(command "_circle" "2237.204,932.7" "0.075")
(command "_circle" "2236.829,932.7" "0.075")
(command "_circle" "2236.454,932.7" "0.075")
(command "_circle" "2236.079,932.7" "0.15")
(command "_circle" "2235.704,932.7" "0.15")
(command "_circle" "2237.954,934.7" "0.075")
(command "_circle" "2237.579,934.7" "0.15")
(command "_circle" "2237.204,934.7" "0.075")
(command "_circle" "2236.829,934.7" "0.075")
(command "_circle" "2236.454,934.7" "0.075")
(command "_circle" "2236.079,934.7" "0.15")
(command "_circle" "2235.704,934.7" "0.15")
(command "_circle" "2237.954,936.7" "0.075")
(command "_circle" "2237.579,936.7" "0.075")
(command "_circle" "2237.204,936.7" "0.15")
(command "_circle" "2236.829,936.7" "0.075")
(command "_circle" "2236.454,936.7" "0.075")
(command "_circle" "2236.079,936.7" "0.15")
(command "_circle" "2235.704,936.7" "0.15")
(command "_circle" "2237.954,938.7" "0.075")
(command "_circle" "2237.579,938.7" "0.15")
(command "_circle" "2237.204,938.7" "0.15")
(command "_circle" "2236.829,938.7" "0.075")
(command "_circle" "2236.454,938.7" "0.075")
(command "_circle" "2236.079,938.7" "0.15")
(command "_circle" "2235.704,938.7" "0.15")
(command "_circle" "2237.954,940.7" "0.075")
(command "_circle" "2237.579,940.7" "0.075")
(command "_circle" "2237.204,940.7" "0.075")
(command "_circle" "2236.829,940.7" "0.15")
(command "_circle" "2236.454,940.7" "0.075")
(command "_circle" "2236.079,940.7" "0.15")
(command "_circle" "2235.704,940.7" "0.15")
(command "_circle" "2237.954,942.7" "0.075")
(command "_circle" "2237.579,942.7" "0.15")
(command "_circle" "2237.204,942.7" "0.075")
(command "_circle" "2236.829,942.7" "0.15")
(command "_circle" "2236.454,942.7" "0.075")
(command "_circle" "2236.079,942.7" "0.15")
(command "_circle" "2235.704,942.7" "0.15")
(command "_circle" "2237.954,944.7" "0.075")
(command "_circle" "2237.579,944.7" "0.075")
(command "_circle" "2237.204,944.7" "0.15")
(command "_circle" "2236.829,944.7" "0.15")
(command "_circle" "2236.454,944.7" "0.075")
(command "_circle" "2236.079,944.7" "0.15")
(command "_circle" "2235.704,944.7" "0.15")
(command "_circle" "2237.954,946.7" "0.075")
(command "_circle" "2237.579,946.7" "0.15")
(command "_circle" "2237.204,946.7" "0.15")
(command "_circle" "2236.829,946.7" "0.15")
(command "_circle" "2236.454,946.7" "0.075")
(command "_circle" "2236.079,946.7" "0.15")
(command "_circle" "2235.704,946.7" "0.15")
(command "_circle" "2237.954,948.7" "0.075")
(command "_circle" "2237.579,948.7" "0.075")
(command "_circle" "2237.204,948.7" "0.075")
(command "_circle" "2236.829,948.7" "0.075")
(command "_circle" "2236.454,948.7" "0.15")
(command "_circle" "2236.079,948.7" "0.15")
(command "_circle" "2235.704,948.7" "0.15")
(command "_circle" "2237.954,950.7" "0.075")
(command "_circle" "2237.579,950.7" "0.15")
(command "_circle" "2237.204,950.7" "0.075")
(command "_circle" "2236.829,950.7" "0.075")
(command "_circle" "2236.454,950.7" "0.15")
(command "_circle" "2236.079,950.7" "0.15")
(command "_circle" "2235.704,950.7" "0.15")
(command "_circle" "2237.954,952.7" "0.075")
(command "_circle" "2237.579,952.7" "0.075")
(command "_circle" "2237.204,952.7" "0.15")
(command "_circle" "2236.829,952.7" "0.075")
(command "_circle" "2236.454,952.7" "0.15")
(command "_circle" "2236.079,952.7" "0.15")
(command "_circle" "2235.704,952.7" "0.15")
(command "_circle" "2237.954,954.7" "0.075")
(command "_circle" "2237.579,954.7" "0.15")
(command "_circle" "2237.204,954.7" "0.15")
(command "_circle" "2236.829,954.7" "0.075")
(command "_circle" "2236.454,954.7" "0.15")
(command "_circle" "2236.079,954.7" "0.15")
(command "_circle" "2235.704,954.7" "0.15")
(command "_circle" "2237.954,956.7" "0.075")
(command "_circle" "2237.579,956.7" "0.075")
(command "_circle" "2237.204,956.7" "0.075")
(command "_circle" "2236.829,956.7" "0.15")
(command "_circle" "2236.454,956.7" "0.15")
(command "_circle" "2236.079,956.7" "0.15")
(command "_circle" "2235.704,956.7" "0.15")
(command "_circle" "2237.954,958.7" "0.075")
(command "_circle" "2237.579,958.7" "0.15")
(command "_circle" "2237.204,958.7" "0.075")
(command "_circle" "2236.829,958.7" "0.15")
(command "_circle" "2236.454,958.7" "0.15")
(command "_circle" "2236.079,958.7" "0.15")
(command "_circle" "2235.704,958.7" "0.15")
(command "_circle" "2237.954,960.7" "0.075")
(command "_circle" "2237.579,960.7" "0.075")
(command "_circle" "2237.204,960.7" "0.15")
(command "_circle" "2236.829,960.7" "0.15")
(command "_circle" "2236.454,960.7" "0.15")
(command "_circle" "2236.079,960.7" "0.15")
(command "_circle" "2235.704,960.7" "0.15")
(command "_circle" "2237.954,962.7" "0.075")
(command "_circle" "2237.579,962.7" "0.15")
(command "_circle" "2237.204,962.7" "0.15")
(command "_circle" "2236.829,962.7" "0.15")
(command "_circle" "2236.454,962.7" "0.15")
(command "_circle" "2236.079,962.7" "0.15")
(command "_circle" "2235.704,962.7" "0.15")
(command "_layer" "set" "nitride" "")
(command "_layer" "set" "text" "")
(command-s "_text" "2226.904,963.3" "2" "-90" "a = 370 nm" )
(sssetfirst nil (ssget "_L"))
(if (not (numberp (vl-string-search "Mac" (getvar "platform")))) (c:txtexp))
(command "_layer" "set" "nitride" "")
(command "_layer" "set" "text" "")
(command-s "_text" "2223.904,963.3" "2" "-90" "gap = 270 nm" )
(sssetfirst nil (ssget "_L"))
(if (not (numberp (vl-string-search "Mac" (getvar "platform")))) (c:txtexp))
(command "_layer" "set" "nitride" "")
(command "_layer" "set" "text" "")
(command-s "_text" "2220.904,963.3" "2" "-90" "amplitude = 132 nm" )
(sssetfirst nil (ssget "_L"))
(if (not (numberp (vl-string-search "Mac" (getvar "platform")))) (c:txtexp))
(command "_layer" "set" "nitride" "")
(command "_layer" "set" "text" "")
(command-s "_text" "2217.904,963.3" "2" "-90" "start width = 280 nm" )
(sssetfirst nil (ssget "_L"))
(if (not (numberp (vl-string-search "Mac" (getvar "platform")))) (c:txtexp))
(command "_layer" "set" "nitride" "")
(command "_layer" "set" "text" "")
(command-s "_text" "2214.904,963.3" "2" "-90" "width = 281 nm" )
(sssetfirst nil (ssget "_L"))
(if (not (numberp (vl-string-search "Mac" (getvar "platform")))) (c:txtexp))
(command "_layer" "set" "nitride" "")
(command "_layer" "set" "text" "")
(command-s "_text" "2211.904,963.3" "2" "-90" "taper: 15" )
(sssetfirst nil (ssget "_L"))
(if (not (numberp (vl-string-search "Mac" (getvar "platform")))) (c:txtexp))
(command "_layer" "set" "nitride" "")
(command "_layer" "set" "text" "")
(command-s "_text" "2208.904,963.3" "2" "-90" "nominal: 150" )
(sssetfirst nil (ssget "_L"))
(if (not (numberp (vl-string-search "Mac" (getvar "platform")))) (c:txtexp))
(command "_layer" "set" "nitride" "")
(command "_layer" "set" "indicators" "")
(setq coords (list 
(list 2160.415 940) 
(list 2160.415 920) 
(list 2140.415 900) 
(list 2160.415 880) 
(list 2160.415 860) 
(list 2160.415 900) 
(list 2160.415 887.0711) 
(list 2147.4861 900) 
(list 2160.415 912.9289) 
(list 2160.415 900)))
(apply 'command (append '("pline") coords '("c")))
(command "._fillet" "radius" "1" "._fillet" "P" (entlast))
(setq coords (list 
(list 2319.585 940) 
(list 2319.585 920) 
(list 2339.585 900) 
(list 2319.585 880) 
(list 2319.585 860) 
(list 2319.585 900) 
(list 2319.585 887.0711) 
(list 2332.5139 900) 
(list 2319.585 912.9289) 
(list 2319.585 900)))
(apply 'command (append '("pline") coords '("c")))
(command "._fillet" "radius" "1" "._fillet" "P" (entlast))
(command "_layer" "set" "holes" "")
(command "_circle" "2158.0629,914.1124" "0.5")
(command "_circle" "2155.7109,911.7603" "0.5")
(command "_circle" "2153.3588,909.4083" "0.5")
(command "_circle" "2151.0067,907.0562" "0.5")
(command "_circle" "2148.6547,904.7041" "0.5")
(command "_circle" "2146.3026,902.3521" "0.5")
(command "_circle" "2143.9505,900" "0.5")
(command "_circle" "2146.3026,897.6479" "0.5")
(command "_circle" "2148.6547,895.2959" "0.5")
(command "_circle" "2151.0067,892.9438" "0.5")
(command "_circle" "2153.3588,890.5917" "0.5")
(command "_circle" "2155.7109,888.2397" "0.5")
(command "_circle" "2158.0629,885.8876" "0.5")
(command "_circle" "2321.9371,914.1124" "0.5")
(command "_circle" "2324.2891,911.7603" "0.5")
(command "_circle" "2326.6412,909.4083" "0.5")
(command "_circle" "2328.9933,907.0562" "0.5")
(command "_circle" "2331.3453,904.7041" "0.5")
(command "_circle" "2333.6974,902.3521" "0.5")
(command "_circle" "2336.0495,900" "0.5")
(command "_circle" "2333.6974,897.6479" "0.5")
(command "_circle" "2331.3453,895.2959" "0.5")
(command "_circle" "2328.9933,892.9438" "0.5")
(command "_circle" "2326.6412,890.5917" "0.5")
(command "_circle" "2324.2891,888.2397" "0.5")
(command "_circle" "2321.9371,885.8876" "0.5")
(command "_layer" "set" "nitride" "")
(command "_block" "blkcoupler7" "2240,900" coupler7 "")
(command "_insert" "blkcoupler7" "2240,900" "1" "1" "0")
(command "_insert" "blkcoupler7" "2240,900" "1" "1" "180")
(command "_block" "blksinglenanobeam7" "2240,900" singlenanobeam7 "")
(command "_insert" "blksinglenanobeam7" "2240,900" "1" "1" "0")
(command "_insert" "blksinglenanobeam7" "2240,900" "1" "1" "180")
(command "_block" "blkanglednodearray7" "2240,900" anglednodearray7 "")
(command "_insert" "blkanglednodearray7" "2240,900" "1" "1" "0")
(command "_insert" "blkanglednodearray7" "2240,900" "1" "1" "180")
(command "_block" "blkcooledsinglenanobeam7" "2240,900" cooledsinglenanobeam7 "")
(command "_insert" "blkcooledsinglenanobeam7" "2240,900" "1" "1" "0")
(command "_insert" "blkcooledsinglenanobeam7" "2240,900" "1" "1" "180")
(command "_block" "blkyjunction7" "2240,900" yjunction7 "")
(command "_insert" "blkyjunction7" "2240,900" "1" "1" "0")
(command "_insert" "blkyjunction7" "2240,900" "1" "1" "180")
; DRAWING BULGING VEE GROOVE
(command "_layer" "set" "vgroove" "")
(setq coords (list 
(list 2165.415 -605) 
(list 2165.415 0) 
(list 2165.415 0) 
(list 2165.415 1800) 
(list 2165.415 1800) 
(list 2165.415 2405) 
(list 2314.585 2405) 
(list 2314.585 1800) 
(list 2314.585 1800) 
(list 2314.585 0) 
(list 2314.585 0) 
(list 2314.585 -605)))
(apply 'command (append '("pline") coords '("c")))
(command "._fillet" "radius" "0" "._fillet" "P" (entlast))
(command "_layer" "set" "window" "")
(command "_rectangle" "2165.415,-1935" "2314.585,-600")
(command "_rectangle" "2165.415,2400" "2314.585,5300")
(command "_layer" "set" "grid" "")
(command "_rectangle" "2166.415,-1934" "2189.9433,-1909.2133")
(command "_array" "last" "" "R" "75" "3" "25.7867" "24.5283")
(command "_rectangle" "2241,-1934" "2264.5283,-1909.2133")
(command "_array" "last" "" "R" "75" "3" "25.7867" "24.5283")
(command "_rectangle" "2166.415,1" "2189.9433,25.7")
(command "_array" "last" "" "R" "70" "3" "25.7" "24.5283")
(command "_rectangle" "2241,1" "2264.5283,25.7")
(command "_array" "last" "" "R" "70" "3" "25.7" "24.5283")
(command "_rectangle" "2166.415,1801" "2189.9433,1825.9185")
(command "_array" "last" "" "R" "135" "3" "25.9185" "24.5283")
(command "_rectangle" "2241,1801" "2264.5283,1825.9185")
(command "_array" "last" "" "R" "135" "3" "25.9185" "24.5283")
(command "_layer" "set" "vgrooveFDA" "")
(command "_rectangle" "2314.585,-2233" "2165.415,-1933")
(command "_layer" "set" "nitride" "")
(command "_layer" "set" "holes" "")
(command "_circle" "2317.085,331.5" "0.5")
(command "_array" "last" "" "R" "379" "1" "3" "2.5")
(command "_circle" "2162.915,331.5" "0.5")
(command "_array" "last" "" "R" "379" "1" "3" "-2.5")
(command "_layer" "set" "nitride" "")
(command "_layer" "set" "window" "")
(command "_layer" "set" "window" "")
(command "_rectangle" "2319.585,0" "2480.415,1800")
(command "._fillet" "radius" "20" "._fillet" "P" (entlast))
(command "_layer" "set" "grid" "")
(command "_rectangle" "2320.585,1" "2342.4179,25.7")
(command "_array" "last" "" "R" "70" "7" "25.7" "22.8329")
(command "_layer" "set" "nitride" "")
; DRAWING REGION LAYER
(command "_layer" "set" "regionLayer7" "")
(command "_rectangle" "2160,-460" "2320,2260")
(command "_layer" "set" "nitride" "")
(setq coupler7 nil)
(setq singlenanobeam7 nil)
(setq anglednodearray7 nil)
(setq cooledsinglenanobeam7 nil)
(setq yjunction7 nil)
; DEVICE #8
(command "_layer" "set" "window" "")
(command "_circle" "2472.915,-415" "5")
(command "_circle" "2472.915,-402.5" "5")
(command "_circle" "2472.915,-390" "5")
(command "_circle" "2472.915,-377.5" "5")
(command "_circle" "2460.415,-415" "5")
(command "_circle" "2460.415,-402.5" "5")
(command "_circle" "2460.415,-390" "5")
(command "_circle" "2460.415,-377.5" "5")
(command "_layer" "set" "nitride" "")
(setq currobj nil)
(setq currobj (ssadd))
; DRAWING COUPLER
(setq coords (list 
(list 2560.0615 -415) 
(list 2560.0615 -413) 
(list 2633.585 -413) 
(list 2633.585 -413) 
(list 2633.9677 -413.0761) 
(list 2634.2921 -413.2929) 
(list 2634.5089 -413.6173) 
(list 2634.585 -414) 
(list 2634.585 -411.8) 
(list 2634.585 -411.8) 
(list 2634.5089 -412.1827) 
(list 2634.2921 -412.5071) 
(list 2633.9677 -412.7239) 
(list 2633.585 -412.8) 
(list 2560.0615 -412.8) 
(list 2560.0615 -410.8) 
(list 2559.9385 -410.8) 
(list 2559.9385 -412.8) 
(list 2486.415 -412.8) 
(list 2486.0323 -412.7239) 
(list 2485.7079 -412.5071) 
(list 2485.4911 -412.1827) 
(list 2485.415 -411.8) 
(list 2485.415 -411.8) 
(list 2485.415 -414) 
(list 2485.4911 -413.6173) 
(list 2485.7079 -413.2929) 
(list 2486.0323 -413.0761) 
(list 2486.415 -413) 
(list 2486.415 -413) 
(list 2559.9385 -413) 
(list 2559.9385 -415)))
(apply 'command (append '("pline") coords '("c")))
(setq currobj (ssadd (entlast) currobj))
(command "._fillet" "radius" "0.3" "._fillet" "P" (entlast))
(command "_layer" "set" "holes" "")
(command "_circle" "2560,-412.9" "0.113")
(setq currobj (ssadd (entlast) currobj))
(command "_layer" "set" "nitride" "")
(command "_layer" "set" "text" "")
(command "_circle" "2559.2,-415" "0.075")
(command "_circle" "2559.2,-414.7" "0.075")
(command "_circle" "2559.2,-414.4" "0.075")
(command "_circle" "2558.9,-415" "0.075")
(command "_circle" "2558.9,-414.7" "0.075")
(command "_circle" "2558.9,-414.4" "0.075")
(command "_circle" "2558.6,-415" "0.075")
(command "_circle" "2558.6,-414.7" "0.075")
(command "_circle" "2558.6,-414.4" "0.075")
(command "_layer" "set" "nitride" "")
(command "_layer" "set" "prebias" "")
(command "_rectangle" "2485.415,-414" "2634.585,-411.8")
(setq currobj (ssadd (entlast) currobj))
(command "_rectangle" "2559.9385,-415" "2560.0615,-410.8")
(setq currobj (ssadd (entlast) currobj))
(command "_layer" "set" "nitride" "")
(setq coupler8 currobj)
(setq currobj nil)
(setq currobj (ssadd))
; DRAWING SINGLE NANOBEAM
(setq coords (list 
(list 2560.0615 -410.8) 
(list 2560.0615 -409.1417) 
(list 2560.0615 -407.4833) 
(list 2560.0615 -405.825) 
(list 2560.0615 -404.1667) 
(list 2560.0615 -402.5083) 
(list 2560.0615 -400.85) 
(list 2560.0615 -399.1917) 
(list 2560.0615 -397.5333) 
(list 2560.0616 -395.875) 
(list 2560.0616 -394.2167) 
(list 2560.0616 -392.5583) 
(list 2560.0616 -390.9) 
(list 2560.0617 -389.2417) 
(list 2560.0617 -387.5833) 
(list 2560.0617 -385.925) 
(list 2560.0618 -384.2667) 
(list 2560.0619 -382.6083) 
(list 2560.0619 -380.95) 
(list 2560.062 -379.2917) 
(list 2560.0621 -377.6333) 
(list 2560.0622 -375.975) 
(list 2560.0623 -374.3167) 
(list 2560.0624 -372.6583) 
(list 2560.0625 -371) 
(list 2560.0626 -369.3417) 
(list 2560.0628 -367.6833) 
(list 2560.0629 -366.025) 
(list 2560.0631 -364.3667) 
(list 2560.0632 -362.7083) 
(list 2560.0634 -361.05) 
(list 2560.0636 -359.3917) 
(list 2560.0638 -357.7333) 
(list 2560.0641 -356.075) 
(list 2560.0643 -354.4167) 
(list 2560.0646 -352.7583) 
(list 2560.0648 -351.1) 
(list 2560.0651 -349.4417) 
(list 2560.0654 -347.7833) 
(list 2560.0657 -346.125) 
(list 2560.0661 -344.4667) 
(list 2560.0664 -342.8083) 
(list 2560.0668 -341.15) 
(list 2560.0672 -339.4917) 
(list 2560.0676 -337.8333) 
(list 2560.068 -336.175) 
(list 2560.0685 -334.5167) 
(list 2560.0689 -332.8583) 
(list 2560.0694 -331.2) 
(list 2560.0699 -329.5417) 
(list 2560.0704 -327.8833) 
(list 2560.071 -326.225) 
(list 2560.0715 -324.5667) 
(list 2560.0721 -322.9083) 
(list 2560.0728 -321.25) 
(list 2560.0734 -319.5917) 
(list 2560.0741 -317.9333) 
(list 2560.0747 -316.275) 
(list 2560.0754 -314.6167) 
(list 2560.0762 -312.9583) 
(list 2560.0769 -311.3) 
(list 2560.0777 -309.6417) 
(list 2560.0785 -307.9833) 
(list 2560.0794 -306.325) 
(list 2560.0802 -304.6667) 
(list 2560.0811 -303.0083) 
(list 2560.082 -301.35) 
(list 2560.083 -299.6917) 
(list 2560.084 -298.0333) 
(list 2560.085 -296.375) 
(list 2560.086 -294.7167) 
(list 2560.0871 -293.0583) 
(list 2560.0882 -291.4) 
(list 2560.0893 -289.7417) 
(list 2560.0905 -288.0833) 
(list 2560.0917 -286.425) 
(list 2560.0929 -284.7667) 
(list 2560.0941 -283.1083) 
(list 2560.0954 -281.45) 
(list 2560.0967 -279.7917) 
(list 2560.0981 -278.1333) 
(list 2560.0995 -276.475) 
(list 2560.1009 -274.8167) 
(list 2560.1024 -273.1583) 
(list 2560.1039 -271.5) 
(list 2560.1054 -269.8417) 
(list 2560.107 -268.1833) 
(list 2560.1086 -266.525) 
(list 2560.1102 -264.8667) 
(list 2560.1119 -263.2083) 
(list 2560.1136 -261.55) 
(list 2560.1154 -259.8917) 
(list 2560.1172 -258.2333) 
(list 2560.119 -256.575) 
(list 2560.1209 -254.9167) 
(list 2560.1228 -253.2583) 
(list 2560.1247 -251.6) 
(list 2560.1267 -249.9417) 
(list 2560.1288 -248.2833) 
(list 2560.1308 -246.625) 
(list 2560.133 -244.9667) 
(list 2560.1351 -243.3083) 
(list 2560.1373 -241.65) 
(list 2560.1396 -239.9917) 
(list 2560.1419 -238.3333) 
(list 2560.1442 -236.675) 
(list 2560.1466 -235.0167) 
(list 2560.1491 -233.3583) 
(list 2560.1515 -231.7) 
(list 2560.1541 -230.0417) 
(list 2560.1566 -228.3833) 
(list 2560.1592 -226.725) 
(list 2560.1619 -225.0667) 
(list 2560.1646 -223.4083) 
(list 2560.1674 -221.75) 
(list 2560.1702 -220.0917) 
(list 2560.1731 -218.4333) 
(list 2560.176 -216.775) 
(list 2560.1789 -215.1167) 
(list 2560.1819 -213.4583) 
(list 2560.185 -211.8) 
(list 2559.815 -211.8) 
(list 2559.8181 -213.4583) 
(list 2559.8211 -215.1167) 
(list 2559.824 -216.775) 
(list 2559.8269 -218.4333) 
(list 2559.8298 -220.0917) 
(list 2559.8326 -221.75) 
(list 2559.8354 -223.4083) 
(list 2559.8381 -225.0667) 
(list 2559.8408 -226.725) 
(list 2559.8434 -228.3833) 
(list 2559.8459 -230.0417) 
(list 2559.8485 -231.7) 
(list 2559.8509 -233.3583) 
(list 2559.8534 -235.0167) 
(list 2559.8558 -236.675) 
(list 2559.8581 -238.3333) 
(list 2559.8604 -239.9917) 
(list 2559.8627 -241.65) 
(list 2559.8649 -243.3083) 
(list 2559.867 -244.9667) 
(list 2559.8692 -246.625) 
(list 2559.8712 -248.2833) 
(list 2559.8733 -249.9417) 
(list 2559.8753 -251.6) 
(list 2559.8772 -253.2583) 
(list 2559.8791 -254.9167) 
(list 2559.881 -256.575) 
(list 2559.8828 -258.2333) 
(list 2559.8846 -259.8917) 
(list 2559.8864 -261.55) 
(list 2559.8881 -263.2083) 
(list 2559.8898 -264.8667) 
(list 2559.8914 -266.525) 
(list 2559.893 -268.1833) 
(list 2559.8946 -269.8417) 
(list 2559.8961 -271.5) 
(list 2559.8976 -273.1583) 
(list 2559.8991 -274.8167) 
(list 2559.9005 -276.475) 
(list 2559.9019 -278.1333) 
(list 2559.9033 -279.7917) 
(list 2559.9046 -281.45) 
(list 2559.9059 -283.1083) 
(list 2559.9071 -284.7667) 
(list 2559.9083 -286.425) 
(list 2559.9095 -288.0833) 
(list 2559.9107 -289.7417) 
(list 2559.9118 -291.4) 
(list 2559.9129 -293.0583) 
(list 2559.914 -294.7167) 
(list 2559.915 -296.375) 
(list 2559.916 -298.0333) 
(list 2559.917 -299.6917) 
(list 2559.918 -301.35) 
(list 2559.9189 -303.0083) 
(list 2559.9198 -304.6667) 
(list 2559.9206 -306.325) 
(list 2559.9215 -307.9833) 
(list 2559.9223 -309.6417) 
(list 2559.9231 -311.3) 
(list 2559.9238 -312.9583) 
(list 2559.9246 -314.6167) 
(list 2559.9253 -316.275) 
(list 2559.9259 -317.9333) 
(list 2559.9266 -319.5917) 
(list 2559.9272 -321.25) 
(list 2559.9279 -322.9083) 
(list 2559.9285 -324.5667) 
(list 2559.929 -326.225) 
(list 2559.9296 -327.8833) 
(list 2559.9301 -329.5417) 
(list 2559.9306 -331.2) 
(list 2559.9311 -332.8583) 
(list 2559.9315 -334.5167) 
(list 2559.932 -336.175) 
(list 2559.9324 -337.8333) 
(list 2559.9328 -339.4917) 
(list 2559.9332 -341.15) 
(list 2559.9336 -342.8083) 
(list 2559.9339 -344.4667) 
(list 2559.9343 -346.125) 
(list 2559.9346 -347.7833) 
(list 2559.9349 -349.4417) 
(list 2559.9352 -351.1) 
(list 2559.9354 -352.7583) 
(list 2559.9357 -354.4167) 
(list 2559.9359 -356.075) 
(list 2559.9362 -357.7333) 
(list 2559.9364 -359.3917) 
(list 2559.9366 -361.05) 
(list 2559.9368 -362.7083) 
(list 2559.9369 -364.3667) 
(list 2559.9371 -366.025) 
(list 2559.9372 -367.6833) 
(list 2559.9374 -369.3417) 
(list 2559.9375 -371) 
(list 2559.9376 -372.6583) 
(list 2559.9377 -374.3167) 
(list 2559.9378 -375.975) 
(list 2559.9379 -377.6333) 
(list 2559.938 -379.2917) 
(list 2559.9381 -380.95) 
(list 2559.9381 -382.6083) 
(list 2559.9382 -384.2667) 
(list 2559.9383 -385.925) 
(list 2559.9383 -387.5833) 
(list 2559.9383 -389.2417) 
(list 2559.9384 -390.9) 
(list 2559.9384 -392.5583) 
(list 2559.9384 -394.2167) 
(list 2559.9384 -395.875) 
(list 2559.9385 -397.5333) 
(list 2559.9385 -399.1917) 
(list 2559.9385 -400.85) 
(list 2559.9385 -402.5083) 
(list 2559.9385 -404.1667) 
(list 2559.9385 -405.825) 
(list 2559.9385 -407.4833) 
(list 2559.9385 -409.1417) 
(list 2559.9385 -410.8)))
(apply 'command (append '("pline") coords '("c")))
(setq currobj (ssadd (entlast) currobj))
(command "_layer" "set" "prebias" "")
(command "_rectangle" "2559.815,-410.8" "2560.185,-211.8")
(setq currobj (ssadd (entlast) currobj))
(command "_layer" "set" "nitride" "")
(setq singlenanobeam8 currobj)
(setq currobj nil)
(setq currobj (ssadd))
; DRAWING NODE ARRAY
(setq coords (list 
(list 2560.185 -211.8) 
(list 2560.5625 -201.8) 
(list 2560.5625 -201.8) 
(list 2560.5625 -200.8) 
(list 2634.585 -212.6864) 
(list 2634.585 -207.7434) 
(list 2560.5625 -197.357) 
(list 2560.5625 -196.357) 
(list 2560.5625 -196.357) 
(list 2560.2625 -186.357) 
(list 2559.7375 -186.357) 
(list 2559.4375 -196.357) 
(list 2559.4375 -196.357) 
(list 2559.4375 -197.357) 
(list 2485.415 -207.7434) 
(list 2485.415 -212.6864) 
(list 2559.4375 -200.8) 
(list 2559.4375 -201.8) 
(list 2559.4375 -201.8) 
(list 2559.815 -211.8)))
(apply 'command (append '("pline") coords '("c")))
(setq currobj (ssadd (entlast) currobj))
(command "_layer" "set" "prebias" "")
(setq coords (list 
(list 2559.4375 -212.6864) 
(list 2559.4375 -200.8) 
(list 2485.415 -212.6864) 
(list 2485.415 -207.7434) 
(list 2559.4375 -197.357) 
(list 2559.4375 -186.357) 
(list 2560.5625 -186.357) 
(list 2560.5625 -197.357) 
(list 2634.585 -207.7434) 
(list 2634.585 -212.6864) 
(list 2560.5625 -200.8) 
(list 2560.5625 -212.6864)))
(apply 'command (append '("pline") coords '("c")))
(setq currobj (ssadd (entlast) currobj))
(command "_layer" "set" "nitride" "")
(command "_layer" "set" "fda1" "")
(setq coords (list 
(list 2560.5625 -200.657) 
(list 2634.585 -212.5434) 
(list 2634.585 -212.3664) 
(list 2560.5625 -200.58)))
(apply 'command (append '("pline") coords '("c")))
(setq currobj (ssadd (entlast) currobj))
(setq coords (list 
(list 2560.5625 -200.437) 
(list 2634.585 -212.2234) 
(list 2634.585 -212.0464) 
(list 2560.5625 -200.36)))
(apply 'command (append '("pline") coords '("c")))
(setq currobj (ssadd (entlast) currobj))
(setq coords (list 
(list 2560.5625 -200.217) 
(list 2634.585 -211.9034) 
(list 2634.585 -211.7264) 
(list 2560.5625 -200.14)))
(apply 'command (append '("pline") coords '("c")))
(setq currobj (ssadd (entlast) currobj))
(setq coords (list 
(list 2560.5625 -199.997) 
(list 2634.585 -211.5834) 
(list 2634.585 -211.4064) 
(list 2560.5625 -199.92)))
(apply 'command (append '("pline") coords '("c")))
(setq currobj (ssadd (entlast) currobj))
(setq coords (list 
(list 2560.5625 -199.777) 
(list 2634.585 -211.2634) 
(list 2634.585 -211.0864) 
(list 2560.5625 -199.7)))
(apply 'command (append '("pline") coords '("c")))
(setq currobj (ssadd (entlast) currobj))
(setq coords (list 
(list 2560.5625 -199.557) 
(list 2634.585 -210.9434) 
(list 2634.585 -210.7664) 
(list 2560.5625 -199.48)))
(apply 'command (append '("pline") coords '("c")))
(setq currobj (ssadd (entlast) currobj))
(setq coords (list 
(list 2560.5625 -199.337) 
(list 2634.585 -210.6234) 
(list 2634.585 -210.4464) 
(list 2560.5625 -199.26)))
(apply 'command (append '("pline") coords '("c")))
(setq currobj (ssadd (entlast) currobj))
(setq coords (list 
(list 2560.5625 -199.117) 
(list 2634.585 -210.3034) 
(list 2634.585 -210.1264) 
(list 2560.5625 -199.04)))
(apply 'command (append '("pline") coords '("c")))
(setq currobj (ssadd (entlast) currobj))
(setq coords (list 
(list 2560.5625 -198.897) 
(list 2634.585 -209.9834) 
(list 2634.585 -209.8064) 
(list 2560.5625 -198.82)))
(apply 'command (append '("pline") coords '("c")))
(setq currobj (ssadd (entlast) currobj))
(setq coords (list 
(list 2560.5625 -198.677) 
(list 2634.585 -209.6634) 
(list 2634.585 -209.4864) 
(list 2560.5625 -198.6)))
(apply 'command (append '("pline") coords '("c")))
(setq currobj (ssadd (entlast) currobj))
(setq coords (list 
(list 2560.5625 -198.457) 
(list 2634.585 -209.3434) 
(list 2634.585 -209.1664) 
(list 2560.5625 -198.38)))
(apply 'command (append '("pline") coords '("c")))
(setq currobj (ssadd (entlast) currobj))
(setq coords (list 
(list 2560.5625 -198.237) 
(list 2634.585 -209.0234) 
(list 2634.585 -208.8464) 
(list 2560.5625 -198.16)))
(apply 'command (append '("pline") coords '("c")))
(setq currobj (ssadd (entlast) currobj))
(setq coords (list 
(list 2560.5625 -198.017) 
(list 2634.585 -208.7034) 
(list 2634.585 -208.5264) 
(list 2560.5625 -197.94)))
(apply 'command (append '("pline") coords '("c")))
(setq currobj (ssadd (entlast) currobj))
(setq coords (list 
(list 2560.5625 -197.797) 
(list 2634.585 -208.3834) 
(list 2634.585 -208.2064) 
(list 2560.5625 -197.72)))
(apply 'command (append '("pline") coords '("c")))
(setq currobj (ssadd (entlast) currobj))
(setq coords (list 
(list 2560.5625 -197.577) 
(list 2634.585 -208.0634) 
(list 2634.585 -207.8864) 
(list 2560.5625 -197.5)))
(apply 'command (append '("pline") coords '("c")))
(setq currobj (ssadd (entlast) currobj))
(setq coords (list 
(list 2559.4375 -197.5) 
(list 2485.415 -207.8864) 
(list 2485.415 -208.0634) 
(list 2559.4375 -197.577)))
(apply 'command (append '("pline") coords '("c")))
(setq currobj (ssadd (entlast) currobj))
(setq coords (list 
(list 2559.4375 -197.72) 
(list 2485.415 -208.2064) 
(list 2485.415 -208.3834) 
(list 2559.4375 -197.797)))
(apply 'command (append '("pline") coords '("c")))
(setq currobj (ssadd (entlast) currobj))
(setq coords (list 
(list 2559.4375 -197.94) 
(list 2485.415 -208.5264) 
(list 2485.415 -208.7034) 
(list 2559.4375 -198.017)))
(apply 'command (append '("pline") coords '("c")))
(setq currobj (ssadd (entlast) currobj))
(setq coords (list 
(list 2559.4375 -198.16) 
(list 2485.415 -208.8464) 
(list 2485.415 -209.0234) 
(list 2559.4375 -198.237)))
(apply 'command (append '("pline") coords '("c")))
(setq currobj (ssadd (entlast) currobj))
(setq coords (list 
(list 2559.4375 -198.38) 
(list 2485.415 -209.1664) 
(list 2485.415 -209.3434) 
(list 2559.4375 -198.457)))
(apply 'command (append '("pline") coords '("c")))
(setq currobj (ssadd (entlast) currobj))
(setq coords (list 
(list 2559.4375 -198.6) 
(list 2485.415 -209.4864) 
(list 2485.415 -209.6634) 
(list 2559.4375 -198.677)))
(apply 'command (append '("pline") coords '("c")))
(setq currobj (ssadd (entlast) currobj))
(setq coords (list 
(list 2559.4375 -198.82) 
(list 2485.415 -209.8064) 
(list 2485.415 -209.9834) 
(list 2559.4375 -198.897)))
(apply 'command (append '("pline") coords '("c")))
(setq currobj (ssadd (entlast) currobj))
(setq coords (list 
(list 2559.4375 -199.04) 
(list 2485.415 -210.1264) 
(list 2485.415 -210.3034) 
(list 2559.4375 -199.117)))
(apply 'command (append '("pline") coords '("c")))
(setq currobj (ssadd (entlast) currobj))
(setq coords (list 
(list 2559.4375 -199.26) 
(list 2485.415 -210.4464) 
(list 2485.415 -210.6234) 
(list 2559.4375 -199.337)))
(apply 'command (append '("pline") coords '("c")))
(setq currobj (ssadd (entlast) currobj))
(setq coords (list 
(list 2559.4375 -199.48) 
(list 2485.415 -210.7664) 
(list 2485.415 -210.9434) 
(list 2559.4375 -199.557)))
(apply 'command (append '("pline") coords '("c")))
(setq currobj (ssadd (entlast) currobj))
(setq coords (list 
(list 2559.4375 -199.7) 
(list 2485.415 -211.0864) 
(list 2485.415 -211.2634) 
(list 2559.4375 -199.777)))
(apply 'command (append '("pline") coords '("c")))
(setq currobj (ssadd (entlast) currobj))
(setq coords (list 
(list 2559.4375 -199.92) 
(list 2485.415 -211.4064) 
(list 2485.415 -211.5834) 
(list 2559.4375 -199.997)))
(apply 'command (append '("pline") coords '("c")))
(setq currobj (ssadd (entlast) currobj))
(setq coords (list 
(list 2559.4375 -200.14) 
(list 2485.415 -211.7264) 
(list 2485.415 -211.9034) 
(list 2559.4375 -200.217)))
(apply 'command (append '("pline") coords '("c")))
(setq currobj (ssadd (entlast) currobj))
(setq coords (list 
(list 2559.4375 -200.36) 
(list 2485.415 -212.0464) 
(list 2485.415 -212.2234) 
(list 2559.4375 -200.437)))
(apply 'command (append '("pline") coords '("c")))
(setq currobj (ssadd (entlast) currobj))
(setq coords (list 
(list 2559.4375 -200.58) 
(list 2485.415 -212.3664) 
(list 2485.415 -212.5434) 
(list 2559.4375 -200.657)))
(apply 'command (append '("pline") coords '("c")))
(setq currobj (ssadd (entlast) currobj))
(command "_layer" "set" "nitride" "")
(command "_layer" "set" "text" "")
(command "_circle" "2558.985,-211.8" "0.075")
(command "_circle" "2558.985,-211.5" "0.075")
(command "_circle" "2558.985,-211.2" "0.075")
(command "_circle" "2558.985,-210.9" "0.075")
(command "_circle" "2558.985,-210.6" "0.075")
(command "_circle" "2558.685,-211.8" "0.075")
(command "_circle" "2558.685,-211.5" "0.075")
(command "_circle" "2558.685,-211.2" "0.075")
(command "_circle" "2558.685,-210.9" "0.075")
(command "_circle" "2558.685,-210.6" "0.075")
(command "_circle" "2558.385,-211.8" "0.075")
(command "_circle" "2558.385,-211.5" "0.075")
(command "_circle" "2558.385,-211.2" "0.075")
(command "_circle" "2558.385,-210.9" "0.075")
(command "_circle" "2558.385,-210.6" "0.075")
(command "_circle" "2558.085,-211.8" "0.075")
(command "_circle" "2558.085,-211.5" "0.075")
(command "_circle" "2558.085,-211.2" "0.075")
(command "_circle" "2558.085,-210.9" "0.075")
(command "_circle" "2558.085,-210.6" "0.075")
(command "_circle" "2557.785,-211.8" "0.075")
(command "_circle" "2557.785,-211.5" "0.075")
(command "_circle" "2557.785,-211.2" "0.075")
(command "_circle" "2557.785,-210.9" "0.075")
(command "_circle" "2557.785,-210.6" "0.075")
(command "_layer" "set" "nitride" "")
(setq anglednodearray8 currobj)
(setq currobj nil)
(setq currobj (ssadd))
; DRAWING COOLED SINGLE NANOBEAM
(setq coords (list 
(list 2560.2625 -186.357) 
(list 2560.2625 -181.357) 
(list 2559.7375 -181.357) 
(list 2559.7375 -186.357)))
(apply 'command (append '("pline") coords '("c")))
(setq currobj (ssadd (entlast) currobj))
(command "_layer" "set" "prebias" "")
(command "_rectangle" "2559.7375,-186.357" "2560.2625,-181.357")
(setq currobj (ssadd (entlast) currobj))
(command "_layer" "set" "nitride" "")
(setq coords (list 
(list 2560.2625 -181.357) 
(list 2560.5625 -171.357) 
(list 2560.5625 -171.357) 
(list 2560.5625 -170.357) 
(list 2634.585 -171.107) 
(list 2634.585 -166.164) 
(list 2560.5625 -166.914) 
(list 2560.5625 -165.914) 
(list 2560.5625 -165.914) 
(list 2560.2625 -155.914) 
(list 2559.7375 -155.914) 
(list 2559.4375 -165.914) 
(list 2559.4375 -165.914) 
(list 2559.4375 -166.914) 
(list 2485.415 -166.164) 
(list 2485.415 -171.107) 
(list 2559.4375 -170.357) 
(list 2559.4375 -171.357) 
(list 2559.4375 -171.357) 
(list 2559.7375 -181.357)))
(apply 'command (append '("pline") coords '("c")))
(setq currobj (ssadd (entlast) currobj))
(command "_layer" "set" "prebias" "")
(setq coords (list 
(list 2559.4375 -181.357) 
(list 2559.4375 -170.357) 
(list 2485.415 -171.107) 
(list 2485.415 -166.164) 
(list 2559.4375 -166.914) 
(list 2559.4375 -155.914) 
(list 2560.5625 -155.914) 
(list 2560.5625 -166.914) 
(list 2634.585 -166.164) 
(list 2634.585 -171.107) 
(list 2560.5625 -170.357) 
(list 2560.5625 -181.357)))
(apply 'command (append '("pline") coords '("c")))
(setq currobj (ssadd (entlast) currobj))
(command "_layer" "set" "nitride" "")
(command "_layer" "set" "fda1" "")
(setq coords (list 
(list 2560.5625 -170.214) 
(list 2634.585 -170.964) 
(list 2634.585 -170.787) 
(list 2560.5625 -170.137)))
(apply 'command (append '("pline") coords '("c")))
(setq currobj (ssadd (entlast) currobj))
(setq coords (list 
(list 2560.5625 -169.994) 
(list 2634.585 -170.644) 
(list 2634.585 -170.467) 
(list 2560.5625 -169.917)))
(apply 'command (append '("pline") coords '("c")))
(setq currobj (ssadd (entlast) currobj))
(setq coords (list 
(list 2560.5625 -169.774) 
(list 2634.585 -170.324) 
(list 2634.585 -170.147) 
(list 2560.5625 -169.697)))
(apply 'command (append '("pline") coords '("c")))
(setq currobj (ssadd (entlast) currobj))
(setq coords (list 
(list 2560.5625 -169.554) 
(list 2634.585 -170.004) 
(list 2634.585 -169.827) 
(list 2560.5625 -169.477)))
(apply 'command (append '("pline") coords '("c")))
(setq currobj (ssadd (entlast) currobj))
(setq coords (list 
(list 2560.5625 -169.334) 
(list 2634.585 -169.684) 
(list 2634.585 -169.507) 
(list 2560.5625 -169.257)))
(apply 'command (append '("pline") coords '("c")))
(setq currobj (ssadd (entlast) currobj))
(setq coords (list 
(list 2560.5625 -169.114) 
(list 2634.585 -169.364) 
(list 2634.585 -169.187) 
(list 2560.5625 -169.037)))
(apply 'command (append '("pline") coords '("c")))
(setq currobj (ssadd (entlast) currobj))
(setq coords (list 
(list 2560.5625 -168.894) 
(list 2634.585 -169.044) 
(list 2634.585 -168.867) 
(list 2560.5625 -168.817)))
(apply 'command (append '("pline") coords '("c")))
(setq currobj (ssadd (entlast) currobj))
(setq coords (list 
(list 2560.5625 -168.674) 
(list 2634.585 -168.724) 
(list 2634.585 -168.547) 
(list 2560.5625 -168.597)))
(apply 'command (append '("pline") coords '("c")))
(setq currobj (ssadd (entlast) currobj))
(setq coords (list 
(list 2560.5625 -168.454) 
(list 2634.585 -168.404) 
(list 2634.585 -168.227) 
(list 2560.5625 -168.377)))
(apply 'command (append '("pline") coords '("c")))
(setq currobj (ssadd (entlast) currobj))
(setq coords (list 
(list 2560.5625 -168.234) 
(list 2634.585 -168.084) 
(list 2634.585 -167.907) 
(list 2560.5625 -168.157)))
(apply 'command (append '("pline") coords '("c")))
(setq currobj (ssadd (entlast) currobj))
(setq coords (list 
(list 2560.5625 -168.014) 
(list 2634.585 -167.764) 
(list 2634.585 -167.587) 
(list 2560.5625 -167.937)))
(apply 'command (append '("pline") coords '("c")))
(setq currobj (ssadd (entlast) currobj))
(setq coords (list 
(list 2560.5625 -167.794) 
(list 2634.585 -167.444) 
(list 2634.585 -167.267) 
(list 2560.5625 -167.717)))
(apply 'command (append '("pline") coords '("c")))
(setq currobj (ssadd (entlast) currobj))
(setq coords (list 
(list 2560.5625 -167.574) 
(list 2634.585 -167.124) 
(list 2634.585 -166.947) 
(list 2560.5625 -167.497)))
(apply 'command (append '("pline") coords '("c")))
(setq currobj (ssadd (entlast) currobj))
(setq coords (list 
(list 2560.5625 -167.354) 
(list 2634.585 -166.804) 
(list 2634.585 -166.627) 
(list 2560.5625 -167.277)))
(apply 'command (append '("pline") coords '("c")))
(setq currobj (ssadd (entlast) currobj))
(setq coords (list 
(list 2560.5625 -167.134) 
(list 2634.585 -166.484) 
(list 2634.585 -166.307) 
(list 2560.5625 -167.057)))
(apply 'command (append '("pline") coords '("c")))
(setq currobj (ssadd (entlast) currobj))
(setq coords (list 
(list 2559.4375 -167.057) 
(list 2485.415 -166.307) 
(list 2485.415 -166.484) 
(list 2559.4375 -167.134)))
(apply 'command (append '("pline") coords '("c")))
(setq currobj (ssadd (entlast) currobj))
(setq coords (list 
(list 2559.4375 -167.277) 
(list 2485.415 -166.627) 
(list 2485.415 -166.804) 
(list 2559.4375 -167.354)))
(apply 'command (append '("pline") coords '("c")))
(setq currobj (ssadd (entlast) currobj))
(setq coords (list 
(list 2559.4375 -167.497) 
(list 2485.415 -166.947) 
(list 2485.415 -167.124) 
(list 2559.4375 -167.574)))
(apply 'command (append '("pline") coords '("c")))
(setq currobj (ssadd (entlast) currobj))
(setq coords (list 
(list 2559.4375 -167.717) 
(list 2485.415 -167.267) 
(list 2485.415 -167.444) 
(list 2559.4375 -167.794)))
(apply 'command (append '("pline") coords '("c")))
(setq currobj (ssadd (entlast) currobj))
(setq coords (list 
(list 2559.4375 -167.937) 
(list 2485.415 -167.587) 
(list 2485.415 -167.764) 
(list 2559.4375 -168.014)))
(apply 'command (append '("pline") coords '("c")))
(setq currobj (ssadd (entlast) currobj))
(setq coords (list 
(list 2559.4375 -168.157) 
(list 2485.415 -167.907) 
(list 2485.415 -168.084) 
(list 2559.4375 -168.234)))
(apply 'command (append '("pline") coords '("c")))
(setq currobj (ssadd (entlast) currobj))
(setq coords (list 
(list 2559.4375 -168.377) 
(list 2485.415 -168.227) 
(list 2485.415 -168.404) 
(list 2559.4375 -168.454)))
(apply 'command (append '("pline") coords '("c")))
(setq currobj (ssadd (entlast) currobj))
(setq coords (list 
(list 2559.4375 -168.597) 
(list 2485.415 -168.547) 
(list 2485.415 -168.724) 
(list 2559.4375 -168.674)))
(apply 'command (append '("pline") coords '("c")))
(setq currobj (ssadd (entlast) currobj))
(setq coords (list 
(list 2559.4375 -168.817) 
(list 2485.415 -168.867) 
(list 2485.415 -169.044) 
(list 2559.4375 -168.894)))
(apply 'command (append '("pline") coords '("c")))
(setq currobj (ssadd (entlast) currobj))
(setq coords (list 
(list 2559.4375 -169.037) 
(list 2485.415 -169.187) 
(list 2485.415 -169.364) 
(list 2559.4375 -169.114)))
(apply 'command (append '("pline") coords '("c")))
(setq currobj (ssadd (entlast) currobj))
(setq coords (list 
(list 2559.4375 -169.257) 
(list 2485.415 -169.507) 
(list 2485.415 -169.684) 
(list 2559.4375 -169.334)))
(apply 'command (append '("pline") coords '("c")))
(setq currobj (ssadd (entlast) currobj))
(setq coords (list 
(list 2559.4375 -169.477) 
(list 2485.415 -169.827) 
(list 2485.415 -170.004) 
(list 2559.4375 -169.554)))
(apply 'command (append '("pline") coords '("c")))
(setq currobj (ssadd (entlast) currobj))
(setq coords (list 
(list 2559.4375 -169.697) 
(list 2485.415 -170.147) 
(list 2485.415 -170.324) 
(list 2559.4375 -169.774)))
(apply 'command (append '("pline") coords '("c")))
(setq currobj (ssadd (entlast) currobj))
(setq coords (list 
(list 2559.4375 -169.917) 
(list 2485.415 -170.467) 
(list 2485.415 -170.644) 
(list 2559.4375 -169.994)))
(apply 'command (append '("pline") coords '("c")))
(setq currobj (ssadd (entlast) currobj))
(setq coords (list 
(list 2559.4375 -170.137) 
(list 2485.415 -170.787) 
(list 2485.415 -170.964) 
(list 2559.4375 -170.214)))
(apply 'command (append '("pline") coords '("c")))
(setq currobj (ssadd (entlast) currobj))
(command "_layer" "set" "nitride" "")
(command "_layer" "set" "text" "")
(command "_circle" "2559.0625,-181.357" "0.075")
(command "_circle" "2559.0625,-181.057" "0.075")
(command "_circle" "2559.0625,-180.757" "0.075")
(command "_circle" "2559.0625,-180.457" "0.075")
(command "_circle" "2559.0625,-180.157" "0.075")
(command "_circle" "2558.7625,-181.357" "0.075")
(command "_circle" "2558.7625,-181.057" "0.075")
(command "_circle" "2558.7625,-180.757" "0.075")
(command "_circle" "2558.7625,-180.457" "0.075")
(command "_circle" "2558.7625,-180.157" "0.075")
(command "_circle" "2558.4625,-181.357" "0.075")
(command "_circle" "2558.4625,-181.057" "0.075")
(command "_circle" "2558.4625,-180.757" "0.075")
(command "_circle" "2558.4625,-180.457" "0.075")
(command "_circle" "2558.4625,-180.157" "0.075")
(command "_circle" "2558.1625,-181.357" "0.075")
(command "_circle" "2558.1625,-181.057" "0.075")
(command "_circle" "2558.1625,-180.757" "0.075")
(command "_circle" "2558.1625,-180.457" "0.075")
(command "_circle" "2558.1625,-180.157" "0.075")
(command "_circle" "2557.8625,-181.357" "0.075")
(command "_circle" "2557.8625,-181.057" "0.075")
(command "_circle" "2557.8625,-180.757" "0.075")
(command "_circle" "2557.8625,-180.457" "0.075")
(command "_circle" "2557.8625,-180.157" "0.075")
(command "_layer" "set" "nitride" "")
(setq coords (list 
(list 2560.2625 -155.914) 
(list 2560.2625 -40.2693) 
(list 2559.7375 -40.2693) 
(list 2559.7375 -155.914)))
(apply 'command (append '("pline") coords '("c")))
(setq currobj (ssadd (entlast) currobj))
(command "_layer" "set" "prebias" "")
(command "_rectangle" "2559.7375,-155.914" "2560.2625,-40.2693")
(setq currobj (ssadd (entlast) currobj))
(command "_layer" "set" "nitride" "")
(setq coords (list 
(list 2560.2625 -40.2693) 
(list 2560.5625 -30.2693) 
(list 2560.5625 -30.2693) 
(list 2560.5625 -29.2693) 
(list 2634.585 -30.0193) 
(list 2634.585 -25.0763) 
(list 2560.5625 -25.8263) 
(list 2560.5625 -24.8263) 
(list 2560.5625 -24.8263) 
(list 2560.2625 -14.8263) 
(list 2559.7375 -14.8263) 
(list 2559.4375 -24.8263) 
(list 2559.4375 -24.8263) 
(list 2559.4375 -25.8263) 
(list 2485.415 -25.0763) 
(list 2485.415 -30.0193) 
(list 2559.4375 -29.2693) 
(list 2559.4375 -30.2693) 
(list 2559.4375 -30.2693) 
(list 2559.7375 -40.2693)))
(apply 'command (append '("pline") coords '("c")))
(setq currobj (ssadd (entlast) currobj))
(command "_layer" "set" "prebias" "")
(setq coords (list 
(list 2559.4375 -40.2693) 
(list 2559.4375 -29.2693) 
(list 2485.415 -30.0193) 
(list 2485.415 -25.0763) 
(list 2559.4375 -25.8263) 
(list 2559.4375 -14.8263) 
(list 2560.5625 -14.8263) 
(list 2560.5625 -25.8263) 
(list 2634.585 -25.0763) 
(list 2634.585 -30.0193) 
(list 2560.5625 -29.2693) 
(list 2560.5625 -40.2693)))
(apply 'command (append '("pline") coords '("c")))
(setq currobj (ssadd (entlast) currobj))
(command "_layer" "set" "nitride" "")
(command "_layer" "set" "fda1" "")
(setq coords (list 
(list 2560.5625 -29.1263) 
(list 2634.585 -29.8763) 
(list 2634.585 -29.6993) 
(list 2560.5625 -29.0493)))
(apply 'command (append '("pline") coords '("c")))
(setq currobj (ssadd (entlast) currobj))
(setq coords (list 
(list 2560.5625 -28.9063) 
(list 2634.585 -29.5563) 
(list 2634.585 -29.3793) 
(list 2560.5625 -28.8293)))
(apply 'command (append '("pline") coords '("c")))
(setq currobj (ssadd (entlast) currobj))
(setq coords (list 
(list 2560.5625 -28.6863) 
(list 2634.585 -29.2363) 
(list 2634.585 -29.0593) 
(list 2560.5625 -28.6093)))
(apply 'command (append '("pline") coords '("c")))
(setq currobj (ssadd (entlast) currobj))
(setq coords (list 
(list 2560.5625 -28.4663) 
(list 2634.585 -28.9163) 
(list 2634.585 -28.7393) 
(list 2560.5625 -28.3893)))
(apply 'command (append '("pline") coords '("c")))
(setq currobj (ssadd (entlast) currobj))
(setq coords (list 
(list 2560.5625 -28.2463) 
(list 2634.585 -28.5963) 
(list 2634.585 -28.4193) 
(list 2560.5625 -28.1693)))
(apply 'command (append '("pline") coords '("c")))
(setq currobj (ssadd (entlast) currobj))
(setq coords (list 
(list 2560.5625 -28.0263) 
(list 2634.585 -28.2763) 
(list 2634.585 -28.0993) 
(list 2560.5625 -27.9493)))
(apply 'command (append '("pline") coords '("c")))
(setq currobj (ssadd (entlast) currobj))
(setq coords (list 
(list 2560.5625 -27.8063) 
(list 2634.585 -27.9563) 
(list 2634.585 -27.7793) 
(list 2560.5625 -27.7293)))
(apply 'command (append '("pline") coords '("c")))
(setq currobj (ssadd (entlast) currobj))
(setq coords (list 
(list 2560.5625 -27.5863) 
(list 2634.585 -27.6363) 
(list 2634.585 -27.4593) 
(list 2560.5625 -27.5093)))
(apply 'command (append '("pline") coords '("c")))
(setq currobj (ssadd (entlast) currobj))
(setq coords (list 
(list 2560.5625 -27.3663) 
(list 2634.585 -27.3163) 
(list 2634.585 -27.1393) 
(list 2560.5625 -27.2893)))
(apply 'command (append '("pline") coords '("c")))
(setq currobj (ssadd (entlast) currobj))
(setq coords (list 
(list 2560.5625 -27.1463) 
(list 2634.585 -26.9963) 
(list 2634.585 -26.8193) 
(list 2560.5625 -27.0693)))
(apply 'command (append '("pline") coords '("c")))
(setq currobj (ssadd (entlast) currobj))
(setq coords (list 
(list 2560.5625 -26.9263) 
(list 2634.585 -26.6763) 
(list 2634.585 -26.4993) 
(list 2560.5625 -26.8493)))
(apply 'command (append '("pline") coords '("c")))
(setq currobj (ssadd (entlast) currobj))
(setq coords (list 
(list 2560.5625 -26.7063) 
(list 2634.585 -26.3563) 
(list 2634.585 -26.1793) 
(list 2560.5625 -26.6293)))
(apply 'command (append '("pline") coords '("c")))
(setq currobj (ssadd (entlast) currobj))
(setq coords (list 
(list 2560.5625 -26.4863) 
(list 2634.585 -26.0363) 
(list 2634.585 -25.8593) 
(list 2560.5625 -26.4093)))
(apply 'command (append '("pline") coords '("c")))
(setq currobj (ssadd (entlast) currobj))
(setq coords (list 
(list 2560.5625 -26.2663) 
(list 2634.585 -25.7163) 
(list 2634.585 -25.5393) 
(list 2560.5625 -26.1893)))
(apply 'command (append '("pline") coords '("c")))
(setq currobj (ssadd (entlast) currobj))
(setq coords (list 
(list 2560.5625 -26.0463) 
(list 2634.585 -25.3963) 
(list 2634.585 -25.2193) 
(list 2560.5625 -25.9693)))
(apply 'command (append '("pline") coords '("c")))
(setq currobj (ssadd (entlast) currobj))
(setq coords (list 
(list 2559.4375 -25.9693) 
(list 2485.415 -25.2193) 
(list 2485.415 -25.3963) 
(list 2559.4375 -26.0463)))
(apply 'command (append '("pline") coords '("c")))
(setq currobj (ssadd (entlast) currobj))
(setq coords (list 
(list 2559.4375 -26.1893) 
(list 2485.415 -25.5393) 
(list 2485.415 -25.7163) 
(list 2559.4375 -26.2663)))
(apply 'command (append '("pline") coords '("c")))
(setq currobj (ssadd (entlast) currobj))
(setq coords (list 
(list 2559.4375 -26.4093) 
(list 2485.415 -25.8593) 
(list 2485.415 -26.0363) 
(list 2559.4375 -26.4863)))
(apply 'command (append '("pline") coords '("c")))
(setq currobj (ssadd (entlast) currobj))
(setq coords (list 
(list 2559.4375 -26.6293) 
(list 2485.415 -26.1793) 
(list 2485.415 -26.3563) 
(list 2559.4375 -26.7063)))
(apply 'command (append '("pline") coords '("c")))
(setq currobj (ssadd (entlast) currobj))
(setq coords (list 
(list 2559.4375 -26.8493) 
(list 2485.415 -26.4993) 
(list 2485.415 -26.6763) 
(list 2559.4375 -26.9263)))
(apply 'command (append '("pline") coords '("c")))
(setq currobj (ssadd (entlast) currobj))
(setq coords (list 
(list 2559.4375 -27.0693) 
(list 2485.415 -26.8193) 
(list 2485.415 -26.9963) 
(list 2559.4375 -27.1463)))
(apply 'command (append '("pline") coords '("c")))
(setq currobj (ssadd (entlast) currobj))
(setq coords (list 
(list 2559.4375 -27.2893) 
(list 2485.415 -27.1393) 
(list 2485.415 -27.3163) 
(list 2559.4375 -27.3663)))
(apply 'command (append '("pline") coords '("c")))
(setq currobj (ssadd (entlast) currobj))
(setq coords (list 
(list 2559.4375 -27.5093) 
(list 2485.415 -27.4593) 
(list 2485.415 -27.6363) 
(list 2559.4375 -27.5863)))
(apply 'command (append '("pline") coords '("c")))
(setq currobj (ssadd (entlast) currobj))
(setq coords (list 
(list 2559.4375 -27.7293) 
(list 2485.415 -27.7793) 
(list 2485.415 -27.9563) 
(list 2559.4375 -27.8063)))
(apply 'command (append '("pline") coords '("c")))
(setq currobj (ssadd (entlast) currobj))
(setq coords (list 
(list 2559.4375 -27.9493) 
(list 2485.415 -28.0993) 
(list 2485.415 -28.2763) 
(list 2559.4375 -28.0263)))
(apply 'command (append '("pline") coords '("c")))
(setq currobj (ssadd (entlast) currobj))
(setq coords (list 
(list 2559.4375 -28.1693) 
(list 2485.415 -28.4193) 
(list 2485.415 -28.5963) 
(list 2559.4375 -28.2463)))
(apply 'command (append '("pline") coords '("c")))
(setq currobj (ssadd (entlast) currobj))
(setq coords (list 
(list 2559.4375 -28.3893) 
(list 2485.415 -28.7393) 
(list 2485.415 -28.9163) 
(list 2559.4375 -28.4663)))
(apply 'command (append '("pline") coords '("c")))
(setq currobj (ssadd (entlast) currobj))
(setq coords (list 
(list 2559.4375 -28.6093) 
(list 2485.415 -29.0593) 
(list 2485.415 -29.2363) 
(list 2559.4375 -28.6863)))
(apply 'command (append '("pline") coords '("c")))
(setq currobj (ssadd (entlast) currobj))
(setq coords (list 
(list 2559.4375 -28.8293) 
(list 2485.415 -29.3793) 
(list 2485.415 -29.5563) 
(list 2559.4375 -28.9063)))
(apply 'command (append '("pline") coords '("c")))
(setq currobj (ssadd (entlast) currobj))
(setq coords (list 
(list 2559.4375 -29.0493) 
(list 2485.415 -29.6993) 
(list 2485.415 -29.8763) 
(list 2559.4375 -29.1263)))
(apply 'command (append '("pline") coords '("c")))
(setq currobj (ssadd (entlast) currobj))
(command "_layer" "set" "nitride" "")
(command "_layer" "set" "text" "")
(command "_circle" "2559.0625,-40.2693" "0.075")
(command "_circle" "2559.0625,-39.9693" "0.075")
(command "_circle" "2559.0625,-39.6693" "0.075")
(command "_circle" "2559.0625,-39.3693" "0.075")
(command "_circle" "2559.0625,-39.0693" "0.075")
(command "_circle" "2558.7625,-40.2693" "0.075")
(command "_circle" "2558.7625,-39.9693" "0.075")
(command "_circle" "2558.7625,-39.6693" "0.075")
(command "_circle" "2558.7625,-39.3693" "0.075")
(command "_circle" "2558.7625,-39.0693" "0.075")
(command "_circle" "2558.4625,-40.2693" "0.075")
(command "_circle" "2558.4625,-39.9693" "0.075")
(command "_circle" "2558.4625,-39.6693" "0.075")
(command "_circle" "2558.4625,-39.3693" "0.075")
(command "_circle" "2558.4625,-39.0693" "0.075")
(command "_circle" "2558.1625,-40.2693" "0.075")
(command "_circle" "2558.1625,-39.9693" "0.075")
(command "_circle" "2558.1625,-39.6693" "0.075")
(command "_circle" "2558.1625,-39.3693" "0.075")
(command "_circle" "2558.1625,-39.0693" "0.075")
(command "_circle" "2557.8625,-40.2693" "0.075")
(command "_circle" "2557.8625,-39.9693" "0.075")
(command "_circle" "2557.8625,-39.6693" "0.075")
(command "_circle" "2557.8625,-39.3693" "0.075")
(command "_circle" "2557.8625,-39.0693" "0.075")
(command "_layer" "set" "nitride" "")
(setq coords (list 
(list 2560.2625 -14.8263) 
(list 2560.2625 100.8184) 
(list 2559.7375 100.8184) 
(list 2559.7375 -14.8263)))
(apply 'command (append '("pline") coords '("c")))
(setq currobj (ssadd (entlast) currobj))
(command "_layer" "set" "prebias" "")
(command "_rectangle" "2559.7375,-14.8263" "2560.2625,100.8184")
(setq currobj (ssadd (entlast) currobj))
(command "_layer" "set" "nitride" "")
(setq coords (list 
(list 2560.2625 100.8184) 
(list 2560.5625 110.8184) 
(list 2560.5625 110.8184) 
(list 2560.5625 111.8184) 
(list 2634.585 111.0684) 
(list 2634.585 116.0114) 
(list 2560.5625 115.2614) 
(list 2560.5625 116.2614) 
(list 2560.5625 116.2614) 
(list 2560.2625 126.2614) 
(list 2559.7375 126.2614) 
(list 2559.4375 116.2614) 
(list 2559.4375 116.2614) 
(list 2559.4375 115.2614) 
(list 2485.415 116.0114) 
(list 2485.415 111.0684) 
(list 2559.4375 111.8184) 
(list 2559.4375 110.8184) 
(list 2559.4375 110.8184) 
(list 2559.7375 100.8184)))
(apply 'command (append '("pline") coords '("c")))
(setq currobj (ssadd (entlast) currobj))
(command "_layer" "set" "prebias" "")
(setq coords (list 
(list 2559.4375 100.8184) 
(list 2559.4375 111.8184) 
(list 2485.415 111.0684) 
(list 2485.415 116.0114) 
(list 2559.4375 115.2614) 
(list 2559.4375 126.2614) 
(list 2560.5625 126.2614) 
(list 2560.5625 115.2614) 
(list 2634.585 116.0114) 
(list 2634.585 111.0684) 
(list 2560.5625 111.8184) 
(list 2560.5625 100.8184)))
(apply 'command (append '("pline") coords '("c")))
(setq currobj (ssadd (entlast) currobj))
(command "_layer" "set" "nitride" "")
(command "_layer" "set" "fda1" "")
(setq coords (list 
(list 2560.5625 111.9614) 
(list 2634.585 111.2114) 
(list 2634.585 111.3884) 
(list 2560.5625 112.0384)))
(apply 'command (append '("pline") coords '("c")))
(setq currobj (ssadd (entlast) currobj))
(setq coords (list 
(list 2560.5625 112.1814) 
(list 2634.585 111.5314) 
(list 2634.585 111.7084) 
(list 2560.5625 112.2584)))
(apply 'command (append '("pline") coords '("c")))
(setq currobj (ssadd (entlast) currobj))
(setq coords (list 
(list 2560.5625 112.4014) 
(list 2634.585 111.8514) 
(list 2634.585 112.0284) 
(list 2560.5625 112.4784)))
(apply 'command (append '("pline") coords '("c")))
(setq currobj (ssadd (entlast) currobj))
(setq coords (list 
(list 2560.5625 112.6214) 
(list 2634.585 112.1714) 
(list 2634.585 112.3484) 
(list 2560.5625 112.6984)))
(apply 'command (append '("pline") coords '("c")))
(setq currobj (ssadd (entlast) currobj))
(setq coords (list 
(list 2560.5625 112.8414) 
(list 2634.585 112.4914) 
(list 2634.585 112.6684) 
(list 2560.5625 112.9184)))
(apply 'command (append '("pline") coords '("c")))
(setq currobj (ssadd (entlast) currobj))
(setq coords (list 
(list 2560.5625 113.0614) 
(list 2634.585 112.8114) 
(list 2634.585 112.9884) 
(list 2560.5625 113.1384)))
(apply 'command (append '("pline") coords '("c")))
(setq currobj (ssadd (entlast) currobj))
(setq coords (list 
(list 2560.5625 113.2814) 
(list 2634.585 113.1314) 
(list 2634.585 113.3084) 
(list 2560.5625 113.3584)))
(apply 'command (append '("pline") coords '("c")))
(setq currobj (ssadd (entlast) currobj))
(setq coords (list 
(list 2560.5625 113.5014) 
(list 2634.585 113.4514) 
(list 2634.585 113.6284) 
(list 2560.5625 113.5784)))
(apply 'command (append '("pline") coords '("c")))
(setq currobj (ssadd (entlast) currobj))
(setq coords (list 
(list 2560.5625 113.7214) 
(list 2634.585 113.7714) 
(list 2634.585 113.9484) 
(list 2560.5625 113.7984)))
(apply 'command (append '("pline") coords '("c")))
(setq currobj (ssadd (entlast) currobj))
(setq coords (list 
(list 2560.5625 113.9414) 
(list 2634.585 114.0914) 
(list 2634.585 114.2684) 
(list 2560.5625 114.0184)))
(apply 'command (append '("pline") coords '("c")))
(setq currobj (ssadd (entlast) currobj))
(setq coords (list 
(list 2560.5625 114.1614) 
(list 2634.585 114.4114) 
(list 2634.585 114.5884) 
(list 2560.5625 114.2384)))
(apply 'command (append '("pline") coords '("c")))
(setq currobj (ssadd (entlast) currobj))
(setq coords (list 
(list 2560.5625 114.3814) 
(list 2634.585 114.7314) 
(list 2634.585 114.9084) 
(list 2560.5625 114.4584)))
(apply 'command (append '("pline") coords '("c")))
(setq currobj (ssadd (entlast) currobj))
(setq coords (list 
(list 2560.5625 114.6014) 
(list 2634.585 115.0514) 
(list 2634.585 115.2284) 
(list 2560.5625 114.6784)))
(apply 'command (append '("pline") coords '("c")))
(setq currobj (ssadd (entlast) currobj))
(setq coords (list 
(list 2560.5625 114.8214) 
(list 2634.585 115.3714) 
(list 2634.585 115.5484) 
(list 2560.5625 114.8984)))
(apply 'command (append '("pline") coords '("c")))
(setq currobj (ssadd (entlast) currobj))
(setq coords (list 
(list 2560.5625 115.0414) 
(list 2634.585 115.6914) 
(list 2634.585 115.8684) 
(list 2560.5625 115.1184)))
(apply 'command (append '("pline") coords '("c")))
(setq currobj (ssadd (entlast) currobj))
(setq coords (list 
(list 2559.4375 115.1184) 
(list 2485.415 115.8684) 
(list 2485.415 115.6914) 
(list 2559.4375 115.0414)))
(apply 'command (append '("pline") coords '("c")))
(setq currobj (ssadd (entlast) currobj))
(setq coords (list 
(list 2559.4375 114.8984) 
(list 2485.415 115.5484) 
(list 2485.415 115.3714) 
(list 2559.4375 114.8214)))
(apply 'command (append '("pline") coords '("c")))
(setq currobj (ssadd (entlast) currobj))
(setq coords (list 
(list 2559.4375 114.6784) 
(list 2485.415 115.2284) 
(list 2485.415 115.0514) 
(list 2559.4375 114.6014)))
(apply 'command (append '("pline") coords '("c")))
(setq currobj (ssadd (entlast) currobj))
(setq coords (list 
(list 2559.4375 114.4584) 
(list 2485.415 114.9084) 
(list 2485.415 114.7314) 
(list 2559.4375 114.3814)))
(apply 'command (append '("pline") coords '("c")))
(setq currobj (ssadd (entlast) currobj))
(setq coords (list 
(list 2559.4375 114.2384) 
(list 2485.415 114.5884) 
(list 2485.415 114.4114) 
(list 2559.4375 114.1614)))
(apply 'command (append '("pline") coords '("c")))
(setq currobj (ssadd (entlast) currobj))
(setq coords (list 
(list 2559.4375 114.0184) 
(list 2485.415 114.2684) 
(list 2485.415 114.0914) 
(list 2559.4375 113.9414)))
(apply 'command (append '("pline") coords '("c")))
(setq currobj (ssadd (entlast) currobj))
(setq coords (list 
(list 2559.4375 113.7984) 
(list 2485.415 113.9484) 
(list 2485.415 113.7714) 
(list 2559.4375 113.7214)))
(apply 'command (append '("pline") coords '("c")))
(setq currobj (ssadd (entlast) currobj))
(setq coords (list 
(list 2559.4375 113.5784) 
(list 2485.415 113.6284) 
(list 2485.415 113.4514) 
(list 2559.4375 113.5014)))
(apply 'command (append '("pline") coords '("c")))
(setq currobj (ssadd (entlast) currobj))
(setq coords (list 
(list 2559.4375 113.3584) 
(list 2485.415 113.3084) 
(list 2485.415 113.1314) 
(list 2559.4375 113.2814)))
(apply 'command (append '("pline") coords '("c")))
(setq currobj (ssadd (entlast) currobj))
(setq coords (list 
(list 2559.4375 113.1384) 
(list 2485.415 112.9884) 
(list 2485.415 112.8114) 
(list 2559.4375 113.0614)))
(apply 'command (append '("pline") coords '("c")))
(setq currobj (ssadd (entlast) currobj))
(setq coords (list 
(list 2559.4375 112.9184) 
(list 2485.415 112.6684) 
(list 2485.415 112.4914) 
(list 2559.4375 112.8414)))
(apply 'command (append '("pline") coords '("c")))
(setq currobj (ssadd (entlast) currobj))
(setq coords (list 
(list 2559.4375 112.6984) 
(list 2485.415 112.3484) 
(list 2485.415 112.1714) 
(list 2559.4375 112.6214)))
(apply 'command (append '("pline") coords '("c")))
(setq currobj (ssadd (entlast) currobj))
(setq coords (list 
(list 2559.4375 112.4784) 
(list 2485.415 112.0284) 
(list 2485.415 111.8514) 
(list 2559.4375 112.4014)))
(apply 'command (append '("pline") coords '("c")))
(setq currobj (ssadd (entlast) currobj))
(setq coords (list 
(list 2559.4375 112.2584) 
(list 2485.415 111.7084) 
(list 2485.415 111.5314) 
(list 2559.4375 112.1814)))
(apply 'command (append '("pline") coords '("c")))
(setq currobj (ssadd (entlast) currobj))
(setq coords (list 
(list 2559.4375 112.0384) 
(list 2485.415 111.3884) 
(list 2485.415 111.2114) 
(list 2559.4375 111.9614)))
(apply 'command (append '("pline") coords '("c")))
(setq currobj (ssadd (entlast) currobj))
(command "_layer" "set" "nitride" "")
(command "_layer" "set" "text" "")
(command "_circle" "2559.0625,100.8184" "0.075")
(command "_circle" "2559.0625,101.1184" "0.075")
(command "_circle" "2559.0625,101.4184" "0.075")
(command "_circle" "2559.0625,101.7184" "0.075")
(command "_circle" "2559.0625,102.0184" "0.075")
(command "_circle" "2558.7625,100.8184" "0.075")
(command "_circle" "2558.7625,101.1184" "0.075")
(command "_circle" "2558.7625,101.4184" "0.075")
(command "_circle" "2558.7625,101.7184" "0.075")
(command "_circle" "2558.7625,102.0184" "0.075")
(command "_circle" "2558.4625,100.8184" "0.075")
(command "_circle" "2558.4625,101.1184" "0.075")
(command "_circle" "2558.4625,101.4184" "0.075")
(command "_circle" "2558.4625,101.7184" "0.075")
(command "_circle" "2558.4625,102.0184" "0.075")
(command "_circle" "2558.1625,100.8184" "0.075")
(command "_circle" "2558.1625,101.1184" "0.075")
(command "_circle" "2558.1625,101.4184" "0.075")
(command "_circle" "2558.1625,101.7184" "0.075")
(command "_circle" "2558.1625,102.0184" "0.075")
(command "_circle" "2557.8625,100.8184" "0.075")
(command "_circle" "2557.8625,101.1184" "0.075")
(command "_circle" "2557.8625,101.4184" "0.075")
(command "_circle" "2557.8625,101.7184" "0.075")
(command "_circle" "2557.8625,102.0184" "0.075")
(command "_layer" "set" "nitride" "")
(setq coords (list 
(list 2560.2625 126.2614) 
(list 2560.2625 241.9061) 
(list 2559.7375 241.9061) 
(list 2559.7375 126.2614)))
(apply 'command (append '("pline") coords '("c")))
(setq currobj (ssadd (entlast) currobj))
(command "_layer" "set" "prebias" "")
(command "_rectangle" "2559.7375,126.2614" "2560.2625,241.9061")
(setq currobj (ssadd (entlast) currobj))
(command "_layer" "set" "nitride" "")
(setq coords (list 
(list 2560.2625 241.9061) 
(list 2560.5625 251.9061) 
(list 2560.5625 251.9061) 
(list 2560.5625 252.9061) 
(list 2634.585 252.1561) 
(list 2634.585 257.0991) 
(list 2560.5625 256.3491) 
(list 2560.5625 257.3491) 
(list 2560.5625 257.3491) 
(list 2560.2625 267.3491) 
(list 2559.7375 267.3491) 
(list 2559.4375 257.3491) 
(list 2559.4375 257.3491) 
(list 2559.4375 256.3491) 
(list 2485.415 257.0991) 
(list 2485.415 252.1561) 
(list 2559.4375 252.9061) 
(list 2559.4375 251.9061) 
(list 2559.4375 251.9061) 
(list 2559.7375 241.9061)))
(apply 'command (append '("pline") coords '("c")))
(setq currobj (ssadd (entlast) currobj))
(command "_layer" "set" "prebias" "")
(setq coords (list 
(list 2559.4375 241.9061) 
(list 2559.4375 252.9061) 
(list 2485.415 252.1561) 
(list 2485.415 257.0991) 
(list 2559.4375 256.3491) 
(list 2559.4375 267.3491) 
(list 2560.5625 267.3491) 
(list 2560.5625 256.3491) 
(list 2634.585 257.0991) 
(list 2634.585 252.1561) 
(list 2560.5625 252.9061) 
(list 2560.5625 241.9061)))
(apply 'command (append '("pline") coords '("c")))
(setq currobj (ssadd (entlast) currobj))
(command "_layer" "set" "nitride" "")
(command "_layer" "set" "fda1" "")
(setq coords (list 
(list 2560.5625 253.0491) 
(list 2634.585 252.2991) 
(list 2634.585 252.4761) 
(list 2560.5625 253.1261)))
(apply 'command (append '("pline") coords '("c")))
(setq currobj (ssadd (entlast) currobj))
(setq coords (list 
(list 2560.5625 253.2691) 
(list 2634.585 252.6191) 
(list 2634.585 252.7961) 
(list 2560.5625 253.3461)))
(apply 'command (append '("pline") coords '("c")))
(setq currobj (ssadd (entlast) currobj))
(setq coords (list 
(list 2560.5625 253.4891) 
(list 2634.585 252.9391) 
(list 2634.585 253.1161) 
(list 2560.5625 253.5661)))
(apply 'command (append '("pline") coords '("c")))
(setq currobj (ssadd (entlast) currobj))
(setq coords (list 
(list 2560.5625 253.7091) 
(list 2634.585 253.2591) 
(list 2634.585 253.4361) 
(list 2560.5625 253.7861)))
(apply 'command (append '("pline") coords '("c")))
(setq currobj (ssadd (entlast) currobj))
(setq coords (list 
(list 2560.5625 253.9291) 
(list 2634.585 253.5791) 
(list 2634.585 253.7561) 
(list 2560.5625 254.0061)))
(apply 'command (append '("pline") coords '("c")))
(setq currobj (ssadd (entlast) currobj))
(setq coords (list 
(list 2560.5625 254.1491) 
(list 2634.585 253.8991) 
(list 2634.585 254.0761) 
(list 2560.5625 254.2261)))
(apply 'command (append '("pline") coords '("c")))
(setq currobj (ssadd (entlast) currobj))
(setq coords (list 
(list 2560.5625 254.3691) 
(list 2634.585 254.2191) 
(list 2634.585 254.3961) 
(list 2560.5625 254.4461)))
(apply 'command (append '("pline") coords '("c")))
(setq currobj (ssadd (entlast) currobj))
(setq coords (list 
(list 2560.5625 254.5891) 
(list 2634.585 254.5391) 
(list 2634.585 254.7161) 
(list 2560.5625 254.6661)))
(apply 'command (append '("pline") coords '("c")))
(setq currobj (ssadd (entlast) currobj))
(setq coords (list 
(list 2560.5625 254.8091) 
(list 2634.585 254.8591) 
(list 2634.585 255.0361) 
(list 2560.5625 254.8861)))
(apply 'command (append '("pline") coords '("c")))
(setq currobj (ssadd (entlast) currobj))
(setq coords (list 
(list 2560.5625 255.0291) 
(list 2634.585 255.1791) 
(list 2634.585 255.3561) 
(list 2560.5625 255.1061)))
(apply 'command (append '("pline") coords '("c")))
(setq currobj (ssadd (entlast) currobj))
(setq coords (list 
(list 2560.5625 255.2491) 
(list 2634.585 255.4991) 
(list 2634.585 255.6761) 
(list 2560.5625 255.3261)))
(apply 'command (append '("pline") coords '("c")))
(setq currobj (ssadd (entlast) currobj))
(setq coords (list 
(list 2560.5625 255.4691) 
(list 2634.585 255.8191) 
(list 2634.585 255.9961) 
(list 2560.5625 255.5461)))
(apply 'command (append '("pline") coords '("c")))
(setq currobj (ssadd (entlast) currobj))
(setq coords (list 
(list 2560.5625 255.6891) 
(list 2634.585 256.1391) 
(list 2634.585 256.3161) 
(list 2560.5625 255.7661)))
(apply 'command (append '("pline") coords '("c")))
(setq currobj (ssadd (entlast) currobj))
(setq coords (list 
(list 2560.5625 255.9091) 
(list 2634.585 256.4591) 
(list 2634.585 256.6361) 
(list 2560.5625 255.9861)))
(apply 'command (append '("pline") coords '("c")))
(setq currobj (ssadd (entlast) currobj))
(setq coords (list 
(list 2560.5625 256.1291) 
(list 2634.585 256.7791) 
(list 2634.585 256.9561) 
(list 2560.5625 256.2061)))
(apply 'command (append '("pline") coords '("c")))
(setq currobj (ssadd (entlast) currobj))
(setq coords (list 
(list 2559.4375 256.2061) 
(list 2485.415 256.9561) 
(list 2485.415 256.7791) 
(list 2559.4375 256.1291)))
(apply 'command (append '("pline") coords '("c")))
(setq currobj (ssadd (entlast) currobj))
(setq coords (list 
(list 2559.4375 255.9861) 
(list 2485.415 256.6361) 
(list 2485.415 256.4591) 
(list 2559.4375 255.9091)))
(apply 'command (append '("pline") coords '("c")))
(setq currobj (ssadd (entlast) currobj))
(setq coords (list 
(list 2559.4375 255.7661) 
(list 2485.415 256.3161) 
(list 2485.415 256.1391) 
(list 2559.4375 255.6891)))
(apply 'command (append '("pline") coords '("c")))
(setq currobj (ssadd (entlast) currobj))
(setq coords (list 
(list 2559.4375 255.5461) 
(list 2485.415 255.9961) 
(list 2485.415 255.8191) 
(list 2559.4375 255.4691)))
(apply 'command (append '("pline") coords '("c")))
(setq currobj (ssadd (entlast) currobj))
(setq coords (list 
(list 2559.4375 255.3261) 
(list 2485.415 255.6761) 
(list 2485.415 255.4991) 
(list 2559.4375 255.2491)))
(apply 'command (append '("pline") coords '("c")))
(setq currobj (ssadd (entlast) currobj))
(setq coords (list 
(list 2559.4375 255.1061) 
(list 2485.415 255.3561) 
(list 2485.415 255.1791) 
(list 2559.4375 255.0291)))
(apply 'command (append '("pline") coords '("c")))
(setq currobj (ssadd (entlast) currobj))
(setq coords (list 
(list 2559.4375 254.8861) 
(list 2485.415 255.0361) 
(list 2485.415 254.8591) 
(list 2559.4375 254.8091)))
(apply 'command (append '("pline") coords '("c")))
(setq currobj (ssadd (entlast) currobj))
(setq coords (list 
(list 2559.4375 254.6661) 
(list 2485.415 254.7161) 
(list 2485.415 254.5391) 
(list 2559.4375 254.5891)))
(apply 'command (append '("pline") coords '("c")))
(setq currobj (ssadd (entlast) currobj))
(setq coords (list 
(list 2559.4375 254.4461) 
(list 2485.415 254.3961) 
(list 2485.415 254.2191) 
(list 2559.4375 254.3691)))
(apply 'command (append '("pline") coords '("c")))
(setq currobj (ssadd (entlast) currobj))
(setq coords (list 
(list 2559.4375 254.2261) 
(list 2485.415 254.0761) 
(list 2485.415 253.8991) 
(list 2559.4375 254.1491)))
(apply 'command (append '("pline") coords '("c")))
(setq currobj (ssadd (entlast) currobj))
(setq coords (list 
(list 2559.4375 254.0061) 
(list 2485.415 253.7561) 
(list 2485.415 253.5791) 
(list 2559.4375 253.9291)))
(apply 'command (append '("pline") coords '("c")))
(setq currobj (ssadd (entlast) currobj))
(setq coords (list 
(list 2559.4375 253.7861) 
(list 2485.415 253.4361) 
(list 2485.415 253.2591) 
(list 2559.4375 253.7091)))
(apply 'command (append '("pline") coords '("c")))
(setq currobj (ssadd (entlast) currobj))
(setq coords (list 
(list 2559.4375 253.5661) 
(list 2485.415 253.1161) 
(list 2485.415 252.9391) 
(list 2559.4375 253.4891)))
(apply 'command (append '("pline") coords '("c")))
(setq currobj (ssadd (entlast) currobj))
(setq coords (list 
(list 2559.4375 253.3461) 
(list 2485.415 252.7961) 
(list 2485.415 252.6191) 
(list 2559.4375 253.2691)))
(apply 'command (append '("pline") coords '("c")))
(setq currobj (ssadd (entlast) currobj))
(setq coords (list 
(list 2559.4375 253.1261) 
(list 2485.415 252.4761) 
(list 2485.415 252.2991) 
(list 2559.4375 253.0491)))
(apply 'command (append '("pline") coords '("c")))
(setq currobj (ssadd (entlast) currobj))
(command "_layer" "set" "nitride" "")
(command "_layer" "set" "text" "")
(command "_circle" "2559.0625,241.9061" "0.075")
(command "_circle" "2559.0625,242.2061" "0.075")
(command "_circle" "2559.0625,242.5061" "0.075")
(command "_circle" "2559.0625,242.8061" "0.075")
(command "_circle" "2559.0625,243.1061" "0.075")
(command "_circle" "2558.7625,241.9061" "0.075")
(command "_circle" "2558.7625,242.2061" "0.075")
(command "_circle" "2558.7625,242.5061" "0.075")
(command "_circle" "2558.7625,242.8061" "0.075")
(command "_circle" "2558.7625,243.1061" "0.075")
(command "_circle" "2558.4625,241.9061" "0.075")
(command "_circle" "2558.4625,242.2061" "0.075")
(command "_circle" "2558.4625,242.5061" "0.075")
(command "_circle" "2558.4625,242.8061" "0.075")
(command "_circle" "2558.4625,243.1061" "0.075")
(command "_circle" "2558.1625,241.9061" "0.075")
(command "_circle" "2558.1625,242.2061" "0.075")
(command "_circle" "2558.1625,242.5061" "0.075")
(command "_circle" "2558.1625,242.8061" "0.075")
(command "_circle" "2558.1625,243.1061" "0.075")
(command "_circle" "2557.8625,241.9061" "0.075")
(command "_circle" "2557.8625,242.2061" "0.075")
(command "_circle" "2557.8625,242.5061" "0.075")
(command "_circle" "2557.8625,242.8061" "0.075")
(command "_circle" "2557.8625,243.1061" "0.075")
(command "_layer" "set" "nitride" "")
(setq coords (list 
(list 2560.2625 267.3491) 
(list 2560.2625 382.9939) 
(list 2559.7375 382.9939) 
(list 2559.7375 267.3491)))
(apply 'command (append '("pline") coords '("c")))
(setq currobj (ssadd (entlast) currobj))
(command "_layer" "set" "prebias" "")
(command "_rectangle" "2559.7375,267.3491" "2560.2625,382.9939")
(setq currobj (ssadd (entlast) currobj))
(command "_layer" "set" "nitride" "")
(setq coords (list 
(list 2560.2625 382.9939) 
(list 2560.5625 392.9939) 
(list 2560.5625 392.9939) 
(list 2560.5625 393.9939) 
(list 2634.585 393.2439) 
(list 2634.585 398.1869) 
(list 2560.5625 397.4369) 
(list 2560.5625 398.4369) 
(list 2560.5625 398.4369) 
(list 2560.2625 408.4369) 
(list 2559.7375 408.4369) 
(list 2559.4375 398.4369) 
(list 2559.4375 398.4369) 
(list 2559.4375 397.4369) 
(list 2485.415 398.1869) 
(list 2485.415 393.2439) 
(list 2559.4375 393.9939) 
(list 2559.4375 392.9939) 
(list 2559.4375 392.9939) 
(list 2559.7375 382.9939)))
(apply 'command (append '("pline") coords '("c")))
(setq currobj (ssadd (entlast) currobj))
(command "_layer" "set" "prebias" "")
(setq coords (list 
(list 2559.4375 382.9939) 
(list 2559.4375 393.9939) 
(list 2485.415 393.2439) 
(list 2485.415 398.1869) 
(list 2559.4375 397.4369) 
(list 2559.4375 408.4369) 
(list 2560.5625 408.4369) 
(list 2560.5625 397.4369) 
(list 2634.585 398.1869) 
(list 2634.585 393.2439) 
(list 2560.5625 393.9939) 
(list 2560.5625 382.9939)))
(apply 'command (append '("pline") coords '("c")))
(setq currobj (ssadd (entlast) currobj))
(command "_layer" "set" "nitride" "")
(command "_layer" "set" "fda1" "")
(setq coords (list 
(list 2560.5625 394.1369) 
(list 2634.585 393.3869) 
(list 2634.585 393.5639) 
(list 2560.5625 394.2139)))
(apply 'command (append '("pline") coords '("c")))
(setq currobj (ssadd (entlast) currobj))
(setq coords (list 
(list 2560.5625 394.3569) 
(list 2634.585 393.7069) 
(list 2634.585 393.8839) 
(list 2560.5625 394.4339)))
(apply 'command (append '("pline") coords '("c")))
(setq currobj (ssadd (entlast) currobj))
(setq coords (list 
(list 2560.5625 394.5769) 
(list 2634.585 394.0269) 
(list 2634.585 394.2039) 
(list 2560.5625 394.6539)))
(apply 'command (append '("pline") coords '("c")))
(setq currobj (ssadd (entlast) currobj))
(setq coords (list 
(list 2560.5625 394.7969) 
(list 2634.585 394.3469) 
(list 2634.585 394.5239) 
(list 2560.5625 394.8739)))
(apply 'command (append '("pline") coords '("c")))
(setq currobj (ssadd (entlast) currobj))
(setq coords (list 
(list 2560.5625 395.0169) 
(list 2634.585 394.6669) 
(list 2634.585 394.8439) 
(list 2560.5625 395.0939)))
(apply 'command (append '("pline") coords '("c")))
(setq currobj (ssadd (entlast) currobj))
(setq coords (list 
(list 2560.5625 395.2369) 
(list 2634.585 394.9869) 
(list 2634.585 395.1639) 
(list 2560.5625 395.3139)))
(apply 'command (append '("pline") coords '("c")))
(setq currobj (ssadd (entlast) currobj))
(setq coords (list 
(list 2560.5625 395.4569) 
(list 2634.585 395.3069) 
(list 2634.585 395.4839) 
(list 2560.5625 395.5339)))
(apply 'command (append '("pline") coords '("c")))
(setq currobj (ssadd (entlast) currobj))
(setq coords (list 
(list 2560.5625 395.6769) 
(list 2634.585 395.6269) 
(list 2634.585 395.8039) 
(list 2560.5625 395.7539)))
(apply 'command (append '("pline") coords '("c")))
(setq currobj (ssadd (entlast) currobj))
(setq coords (list 
(list 2560.5625 395.8969) 
(list 2634.585 395.9469) 
(list 2634.585 396.1239) 
(list 2560.5625 395.9739)))
(apply 'command (append '("pline") coords '("c")))
(setq currobj (ssadd (entlast) currobj))
(setq coords (list 
(list 2560.5625 396.1169) 
(list 2634.585 396.2669) 
(list 2634.585 396.4439) 
(list 2560.5625 396.1939)))
(apply 'command (append '("pline") coords '("c")))
(setq currobj (ssadd (entlast) currobj))
(setq coords (list 
(list 2560.5625 396.3369) 
(list 2634.585 396.5869) 
(list 2634.585 396.7639) 
(list 2560.5625 396.4139)))
(apply 'command (append '("pline") coords '("c")))
(setq currobj (ssadd (entlast) currobj))
(setq coords (list 
(list 2560.5625 396.5569) 
(list 2634.585 396.9069) 
(list 2634.585 397.0839) 
(list 2560.5625 396.6339)))
(apply 'command (append '("pline") coords '("c")))
(setq currobj (ssadd (entlast) currobj))
(setq coords (list 
(list 2560.5625 396.7769) 
(list 2634.585 397.2269) 
(list 2634.585 397.4039) 
(list 2560.5625 396.8539)))
(apply 'command (append '("pline") coords '("c")))
(setq currobj (ssadd (entlast) currobj))
(setq coords (list 
(list 2560.5625 396.9969) 
(list 2634.585 397.5469) 
(list 2634.585 397.7239) 
(list 2560.5625 397.0739)))
(apply 'command (append '("pline") coords '("c")))
(setq currobj (ssadd (entlast) currobj))
(setq coords (list 
(list 2560.5625 397.2169) 
(list 2634.585 397.8669) 
(list 2634.585 398.0439) 
(list 2560.5625 397.2939)))
(apply 'command (append '("pline") coords '("c")))
(setq currobj (ssadd (entlast) currobj))
(setq coords (list 
(list 2559.4375 397.2939) 
(list 2485.415 398.0439) 
(list 2485.415 397.8669) 
(list 2559.4375 397.2169)))
(apply 'command (append '("pline") coords '("c")))
(setq currobj (ssadd (entlast) currobj))
(setq coords (list 
(list 2559.4375 397.0739) 
(list 2485.415 397.7239) 
(list 2485.415 397.5469) 
(list 2559.4375 396.9969)))
(apply 'command (append '("pline") coords '("c")))
(setq currobj (ssadd (entlast) currobj))
(setq coords (list 
(list 2559.4375 396.8539) 
(list 2485.415 397.4039) 
(list 2485.415 397.2269) 
(list 2559.4375 396.7769)))
(apply 'command (append '("pline") coords '("c")))
(setq currobj (ssadd (entlast) currobj))
(setq coords (list 
(list 2559.4375 396.6339) 
(list 2485.415 397.0839) 
(list 2485.415 396.9069) 
(list 2559.4375 396.5569)))
(apply 'command (append '("pline") coords '("c")))
(setq currobj (ssadd (entlast) currobj))
(setq coords (list 
(list 2559.4375 396.4139) 
(list 2485.415 396.7639) 
(list 2485.415 396.5869) 
(list 2559.4375 396.3369)))
(apply 'command (append '("pline") coords '("c")))
(setq currobj (ssadd (entlast) currobj))
(setq coords (list 
(list 2559.4375 396.1939) 
(list 2485.415 396.4439) 
(list 2485.415 396.2669) 
(list 2559.4375 396.1169)))
(apply 'command (append '("pline") coords '("c")))
(setq currobj (ssadd (entlast) currobj))
(setq coords (list 
(list 2559.4375 395.9739) 
(list 2485.415 396.1239) 
(list 2485.415 395.9469) 
(list 2559.4375 395.8969)))
(apply 'command (append '("pline") coords '("c")))
(setq currobj (ssadd (entlast) currobj))
(setq coords (list 
(list 2559.4375 395.7539) 
(list 2485.415 395.8039) 
(list 2485.415 395.6269) 
(list 2559.4375 395.6769)))
(apply 'command (append '("pline") coords '("c")))
(setq currobj (ssadd (entlast) currobj))
(setq coords (list 
(list 2559.4375 395.5339) 
(list 2485.415 395.4839) 
(list 2485.415 395.3069) 
(list 2559.4375 395.4569)))
(apply 'command (append '("pline") coords '("c")))
(setq currobj (ssadd (entlast) currobj))
(setq coords (list 
(list 2559.4375 395.3139) 
(list 2485.415 395.1639) 
(list 2485.415 394.9869) 
(list 2559.4375 395.2369)))
(apply 'command (append '("pline") coords '("c")))
(setq currobj (ssadd (entlast) currobj))
(setq coords (list 
(list 2559.4375 395.0939) 
(list 2485.415 394.8439) 
(list 2485.415 394.6669) 
(list 2559.4375 395.0169)))
(apply 'command (append '("pline") coords '("c")))
(setq currobj (ssadd (entlast) currobj))
(setq coords (list 
(list 2559.4375 394.8739) 
(list 2485.415 394.5239) 
(list 2485.415 394.3469) 
(list 2559.4375 394.7969)))
(apply 'command (append '("pline") coords '("c")))
(setq currobj (ssadd (entlast) currobj))
(setq coords (list 
(list 2559.4375 394.6539) 
(list 2485.415 394.2039) 
(list 2485.415 394.0269) 
(list 2559.4375 394.5769)))
(apply 'command (append '("pline") coords '("c")))
(setq currobj (ssadd (entlast) currobj))
(setq coords (list 
(list 2559.4375 394.4339) 
(list 2485.415 393.8839) 
(list 2485.415 393.7069) 
(list 2559.4375 394.3569)))
(apply 'command (append '("pline") coords '("c")))
(setq currobj (ssadd (entlast) currobj))
(setq coords (list 
(list 2559.4375 394.2139) 
(list 2485.415 393.5639) 
(list 2485.415 393.3869) 
(list 2559.4375 394.1369)))
(apply 'command (append '("pline") coords '("c")))
(setq currobj (ssadd (entlast) currobj))
(command "_layer" "set" "nitride" "")
(command "_layer" "set" "text" "")
(command "_circle" "2559.0625,382.9939" "0.075")
(command "_circle" "2559.0625,383.2939" "0.075")
(command "_circle" "2559.0625,383.5939" "0.075")
(command "_circle" "2559.0625,383.8939" "0.075")
(command "_circle" "2559.0625,384.1939" "0.075")
(command "_circle" "2558.7625,382.9939" "0.075")
(command "_circle" "2558.7625,383.2939" "0.075")
(command "_circle" "2558.7625,383.5939" "0.075")
(command "_circle" "2558.7625,383.8939" "0.075")
(command "_circle" "2558.7625,384.1939" "0.075")
(command "_circle" "2558.4625,382.9939" "0.075")
(command "_circle" "2558.4625,383.2939" "0.075")
(command "_circle" "2558.4625,383.5939" "0.075")
(command "_circle" "2558.4625,383.8939" "0.075")
(command "_circle" "2558.4625,384.1939" "0.075")
(command "_circle" "2558.1625,382.9939" "0.075")
(command "_circle" "2558.1625,383.2939" "0.075")
(command "_circle" "2558.1625,383.5939" "0.075")
(command "_circle" "2558.1625,383.8939" "0.075")
(command "_circle" "2558.1625,384.1939" "0.075")
(command "_circle" "2557.8625,382.9939" "0.075")
(command "_circle" "2557.8625,383.2939" "0.075")
(command "_circle" "2557.8625,383.5939" "0.075")
(command "_circle" "2557.8625,383.8939" "0.075")
(command "_circle" "2557.8625,384.1939" "0.075")
(command "_layer" "set" "nitride" "")
(setq coords (list 
(list 2560.2625 408.4369) 
(list 2560.2625 524.0816) 
(list 2559.7375 524.0816) 
(list 2559.7375 408.4369)))
(apply 'command (append '("pline") coords '("c")))
(setq currobj (ssadd (entlast) currobj))
(command "_layer" "set" "prebias" "")
(command "_rectangle" "2559.7375,408.4369" "2560.2625,524.0816")
(setq currobj (ssadd (entlast) currobj))
(command "_layer" "set" "nitride" "")
(setq coords (list 
(list 2560.2625 524.0816) 
(list 2560.5625 534.0816) 
(list 2560.5625 534.0816) 
(list 2560.5625 535.0816) 
(list 2634.585 534.3316) 
(list 2634.585 539.2746) 
(list 2560.5625 538.5246) 
(list 2560.5625 539.5246) 
(list 2560.5625 539.5246) 
(list 2560.2625 549.5246) 
(list 2559.7375 549.5246) 
(list 2559.4375 539.5246) 
(list 2559.4375 539.5246) 
(list 2559.4375 538.5246) 
(list 2485.415 539.2746) 
(list 2485.415 534.3316) 
(list 2559.4375 535.0816) 
(list 2559.4375 534.0816) 
(list 2559.4375 534.0816) 
(list 2559.7375 524.0816)))
(apply 'command (append '("pline") coords '("c")))
(setq currobj (ssadd (entlast) currobj))
(command "_layer" "set" "prebias" "")
(setq coords (list 
(list 2559.4375 524.0816) 
(list 2559.4375 535.0816) 
(list 2485.415 534.3316) 
(list 2485.415 539.2746) 
(list 2559.4375 538.5246) 
(list 2559.4375 549.5246) 
(list 2560.5625 549.5246) 
(list 2560.5625 538.5246) 
(list 2634.585 539.2746) 
(list 2634.585 534.3316) 
(list 2560.5625 535.0816) 
(list 2560.5625 524.0816)))
(apply 'command (append '("pline") coords '("c")))
(setq currobj (ssadd (entlast) currobj))
(command "_layer" "set" "nitride" "")
(command "_layer" "set" "fda1" "")
(setq coords (list 
(list 2560.5625 535.2246) 
(list 2634.585 534.4746) 
(list 2634.585 534.6516) 
(list 2560.5625 535.3016)))
(apply 'command (append '("pline") coords '("c")))
(setq currobj (ssadd (entlast) currobj))
(setq coords (list 
(list 2560.5625 535.4446) 
(list 2634.585 534.7946) 
(list 2634.585 534.9716) 
(list 2560.5625 535.5216)))
(apply 'command (append '("pline") coords '("c")))
(setq currobj (ssadd (entlast) currobj))
(setq coords (list 
(list 2560.5625 535.6646) 
(list 2634.585 535.1146) 
(list 2634.585 535.2916) 
(list 2560.5625 535.7416)))
(apply 'command (append '("pline") coords '("c")))
(setq currobj (ssadd (entlast) currobj))
(setq coords (list 
(list 2560.5625 535.8846) 
(list 2634.585 535.4346) 
(list 2634.585 535.6116) 
(list 2560.5625 535.9616)))
(apply 'command (append '("pline") coords '("c")))
(setq currobj (ssadd (entlast) currobj))
(setq coords (list 
(list 2560.5625 536.1046) 
(list 2634.585 535.7546) 
(list 2634.585 535.9316) 
(list 2560.5625 536.1816)))
(apply 'command (append '("pline") coords '("c")))
(setq currobj (ssadd (entlast) currobj))
(setq coords (list 
(list 2560.5625 536.3246) 
(list 2634.585 536.0746) 
(list 2634.585 536.2516) 
(list 2560.5625 536.4016)))
(apply 'command (append '("pline") coords '("c")))
(setq currobj (ssadd (entlast) currobj))
(setq coords (list 
(list 2560.5625 536.5446) 
(list 2634.585 536.3946) 
(list 2634.585 536.5716) 
(list 2560.5625 536.6216)))
(apply 'command (append '("pline") coords '("c")))
(setq currobj (ssadd (entlast) currobj))
(setq coords (list 
(list 2560.5625 536.7646) 
(list 2634.585 536.7146) 
(list 2634.585 536.8916) 
(list 2560.5625 536.8416)))
(apply 'command (append '("pline") coords '("c")))
(setq currobj (ssadd (entlast) currobj))
(setq coords (list 
(list 2560.5625 536.9846) 
(list 2634.585 537.0346) 
(list 2634.585 537.2116) 
(list 2560.5625 537.0616)))
(apply 'command (append '("pline") coords '("c")))
(setq currobj (ssadd (entlast) currobj))
(setq coords (list 
(list 2560.5625 537.2046) 
(list 2634.585 537.3546) 
(list 2634.585 537.5316) 
(list 2560.5625 537.2816)))
(apply 'command (append '("pline") coords '("c")))
(setq currobj (ssadd (entlast) currobj))
(setq coords (list 
(list 2560.5625 537.4246) 
(list 2634.585 537.6746) 
(list 2634.585 537.8516) 
(list 2560.5625 537.5016)))
(apply 'command (append '("pline") coords '("c")))
(setq currobj (ssadd (entlast) currobj))
(setq coords (list 
(list 2560.5625 537.6446) 
(list 2634.585 537.9946) 
(list 2634.585 538.1716) 
(list 2560.5625 537.7216)))
(apply 'command (append '("pline") coords '("c")))
(setq currobj (ssadd (entlast) currobj))
(setq coords (list 
(list 2560.5625 537.8646) 
(list 2634.585 538.3146) 
(list 2634.585 538.4916) 
(list 2560.5625 537.9416)))
(apply 'command (append '("pline") coords '("c")))
(setq currobj (ssadd (entlast) currobj))
(setq coords (list 
(list 2560.5625 538.0846) 
(list 2634.585 538.6346) 
(list 2634.585 538.8116) 
(list 2560.5625 538.1616)))
(apply 'command (append '("pline") coords '("c")))
(setq currobj (ssadd (entlast) currobj))
(setq coords (list 
(list 2560.5625 538.3046) 
(list 2634.585 538.9546) 
(list 2634.585 539.1316) 
(list 2560.5625 538.3816)))
(apply 'command (append '("pline") coords '("c")))
(setq currobj (ssadd (entlast) currobj))
(setq coords (list 
(list 2559.4375 538.3816) 
(list 2485.415 539.1316) 
(list 2485.415 538.9546) 
(list 2559.4375 538.3046)))
(apply 'command (append '("pline") coords '("c")))
(setq currobj (ssadd (entlast) currobj))
(setq coords (list 
(list 2559.4375 538.1616) 
(list 2485.415 538.8116) 
(list 2485.415 538.6346) 
(list 2559.4375 538.0846)))
(apply 'command (append '("pline") coords '("c")))
(setq currobj (ssadd (entlast) currobj))
(setq coords (list 
(list 2559.4375 537.9416) 
(list 2485.415 538.4916) 
(list 2485.415 538.3146) 
(list 2559.4375 537.8646)))
(apply 'command (append '("pline") coords '("c")))
(setq currobj (ssadd (entlast) currobj))
(setq coords (list 
(list 2559.4375 537.7216) 
(list 2485.415 538.1716) 
(list 2485.415 537.9946) 
(list 2559.4375 537.6446)))
(apply 'command (append '("pline") coords '("c")))
(setq currobj (ssadd (entlast) currobj))
(setq coords (list 
(list 2559.4375 537.5016) 
(list 2485.415 537.8516) 
(list 2485.415 537.6746) 
(list 2559.4375 537.4246)))
(apply 'command (append '("pline") coords '("c")))
(setq currobj (ssadd (entlast) currobj))
(setq coords (list 
(list 2559.4375 537.2816) 
(list 2485.415 537.5316) 
(list 2485.415 537.3546) 
(list 2559.4375 537.2046)))
(apply 'command (append '("pline") coords '("c")))
(setq currobj (ssadd (entlast) currobj))
(setq coords (list 
(list 2559.4375 537.0616) 
(list 2485.415 537.2116) 
(list 2485.415 537.0346) 
(list 2559.4375 536.9846)))
(apply 'command (append '("pline") coords '("c")))
(setq currobj (ssadd (entlast) currobj))
(setq coords (list 
(list 2559.4375 536.8416) 
(list 2485.415 536.8916) 
(list 2485.415 536.7146) 
(list 2559.4375 536.7646)))
(apply 'command (append '("pline") coords '("c")))
(setq currobj (ssadd (entlast) currobj))
(setq coords (list 
(list 2559.4375 536.6216) 
(list 2485.415 536.5716) 
(list 2485.415 536.3946) 
(list 2559.4375 536.5446)))
(apply 'command (append '("pline") coords '("c")))
(setq currobj (ssadd (entlast) currobj))
(setq coords (list 
(list 2559.4375 536.4016) 
(list 2485.415 536.2516) 
(list 2485.415 536.0746) 
(list 2559.4375 536.3246)))
(apply 'command (append '("pline") coords '("c")))
(setq currobj (ssadd (entlast) currobj))
(setq coords (list 
(list 2559.4375 536.1816) 
(list 2485.415 535.9316) 
(list 2485.415 535.7546) 
(list 2559.4375 536.1046)))
(apply 'command (append '("pline") coords '("c")))
(setq currobj (ssadd (entlast) currobj))
(setq coords (list 
(list 2559.4375 535.9616) 
(list 2485.415 535.6116) 
(list 2485.415 535.4346) 
(list 2559.4375 535.8846)))
(apply 'command (append '("pline") coords '("c")))
(setq currobj (ssadd (entlast) currobj))
(setq coords (list 
(list 2559.4375 535.7416) 
(list 2485.415 535.2916) 
(list 2485.415 535.1146) 
(list 2559.4375 535.6646)))
(apply 'command (append '("pline") coords '("c")))
(setq currobj (ssadd (entlast) currobj))
(setq coords (list 
(list 2559.4375 535.5216) 
(list 2485.415 534.9716) 
(list 2485.415 534.7946) 
(list 2559.4375 535.4446)))
(apply 'command (append '("pline") coords '("c")))
(setq currobj (ssadd (entlast) currobj))
(setq coords (list 
(list 2559.4375 535.3016) 
(list 2485.415 534.6516) 
(list 2485.415 534.4746) 
(list 2559.4375 535.2246)))
(apply 'command (append '("pline") coords '("c")))
(setq currobj (ssadd (entlast) currobj))
(command "_layer" "set" "nitride" "")
(command "_layer" "set" "text" "")
(command "_circle" "2559.0625,524.0816" "0.075")
(command "_circle" "2559.0625,524.3816" "0.075")
(command "_circle" "2559.0625,524.6816" "0.075")
(command "_circle" "2559.0625,524.9816" "0.075")
(command "_circle" "2559.0625,525.2816" "0.075")
(command "_circle" "2558.7625,524.0816" "0.075")
(command "_circle" "2558.7625,524.3816" "0.075")
(command "_circle" "2558.7625,524.6816" "0.075")
(command "_circle" "2558.7625,524.9816" "0.075")
(command "_circle" "2558.7625,525.2816" "0.075")
(command "_circle" "2558.4625,524.0816" "0.075")
(command "_circle" "2558.4625,524.3816" "0.075")
(command "_circle" "2558.4625,524.6816" "0.075")
(command "_circle" "2558.4625,524.9816" "0.075")
(command "_circle" "2558.4625,525.2816" "0.075")
(command "_circle" "2558.1625,524.0816" "0.075")
(command "_circle" "2558.1625,524.3816" "0.075")
(command "_circle" "2558.1625,524.6816" "0.075")
(command "_circle" "2558.1625,524.9816" "0.075")
(command "_circle" "2558.1625,525.2816" "0.075")
(command "_circle" "2557.8625,524.0816" "0.075")
(command "_circle" "2557.8625,524.3816" "0.075")
(command "_circle" "2557.8625,524.6816" "0.075")
(command "_circle" "2557.8625,524.9816" "0.075")
(command "_circle" "2557.8625,525.2816" "0.075")
(command "_layer" "set" "nitride" "")
(setq coords (list 
(list 2560.2625 549.5246) 
(list 2560.2625 665.1693) 
(list 2559.7375 665.1693) 
(list 2559.7375 549.5246)))
(apply 'command (append '("pline") coords '("c")))
(setq currobj (ssadd (entlast) currobj))
(command "_layer" "set" "prebias" "")
(command "_rectangle" "2559.7375,549.5246" "2560.2625,665.1693")
(setq currobj (ssadd (entlast) currobj))
(command "_layer" "set" "nitride" "")
(setq coords (list 
(list 2560.2625 665.1693) 
(list 2560.5625 675.1693) 
(list 2560.5625 675.1693) 
(list 2560.5625 676.1693) 
(list 2634.585 675.4193) 
(list 2634.585 680.3623) 
(list 2560.5625 679.6123) 
(list 2560.5625 680.6123) 
(list 2560.5625 680.6123) 
(list 2560.2625 690.6123) 
(list 2559.7375 690.6123) 
(list 2559.4375 680.6123) 
(list 2559.4375 680.6123) 
(list 2559.4375 679.6123) 
(list 2485.415 680.3623) 
(list 2485.415 675.4193) 
(list 2559.4375 676.1693) 
(list 2559.4375 675.1693) 
(list 2559.4375 675.1693) 
(list 2559.7375 665.1693)))
(apply 'command (append '("pline") coords '("c")))
(setq currobj (ssadd (entlast) currobj))
(command "_layer" "set" "prebias" "")
(setq coords (list 
(list 2559.4375 665.1693) 
(list 2559.4375 676.1693) 
(list 2485.415 675.4193) 
(list 2485.415 680.3623) 
(list 2559.4375 679.6123) 
(list 2559.4375 690.6123) 
(list 2560.5625 690.6123) 
(list 2560.5625 679.6123) 
(list 2634.585 680.3623) 
(list 2634.585 675.4193) 
(list 2560.5625 676.1693) 
(list 2560.5625 665.1693)))
(apply 'command (append '("pline") coords '("c")))
(setq currobj (ssadd (entlast) currobj))
(command "_layer" "set" "nitride" "")
(command "_layer" "set" "fda1" "")
(setq coords (list 
(list 2560.5625 676.3123) 
(list 2634.585 675.5623) 
(list 2634.585 675.7393) 
(list 2560.5625 676.3893)))
(apply 'command (append '("pline") coords '("c")))
(setq currobj (ssadd (entlast) currobj))
(setq coords (list 
(list 2560.5625 676.5323) 
(list 2634.585 675.8823) 
(list 2634.585 676.0593) 
(list 2560.5625 676.6093)))
(apply 'command (append '("pline") coords '("c")))
(setq currobj (ssadd (entlast) currobj))
(setq coords (list 
(list 2560.5625 676.7523) 
(list 2634.585 676.2023) 
(list 2634.585 676.3793) 
(list 2560.5625 676.8293)))
(apply 'command (append '("pline") coords '("c")))
(setq currobj (ssadd (entlast) currobj))
(setq coords (list 
(list 2560.5625 676.9723) 
(list 2634.585 676.5223) 
(list 2634.585 676.6993) 
(list 2560.5625 677.0493)))
(apply 'command (append '("pline") coords '("c")))
(setq currobj (ssadd (entlast) currobj))
(setq coords (list 
(list 2560.5625 677.1923) 
(list 2634.585 676.8423) 
(list 2634.585 677.0193) 
(list 2560.5625 677.2693)))
(apply 'command (append '("pline") coords '("c")))
(setq currobj (ssadd (entlast) currobj))
(setq coords (list 
(list 2560.5625 677.4123) 
(list 2634.585 677.1623) 
(list 2634.585 677.3393) 
(list 2560.5625 677.4893)))
(apply 'command (append '("pline") coords '("c")))
(setq currobj (ssadd (entlast) currobj))
(setq coords (list 
(list 2560.5625 677.6323) 
(list 2634.585 677.4823) 
(list 2634.585 677.6593) 
(list 2560.5625 677.7093)))
(apply 'command (append '("pline") coords '("c")))
(setq currobj (ssadd (entlast) currobj))
(setq coords (list 
(list 2560.5625 677.8523) 
(list 2634.585 677.8023) 
(list 2634.585 677.9793) 
(list 2560.5625 677.9293)))
(apply 'command (append '("pline") coords '("c")))
(setq currobj (ssadd (entlast) currobj))
(setq coords (list 
(list 2560.5625 678.0723) 
(list 2634.585 678.1223) 
(list 2634.585 678.2993) 
(list 2560.5625 678.1493)))
(apply 'command (append '("pline") coords '("c")))
(setq currobj (ssadd (entlast) currobj))
(setq coords (list 
(list 2560.5625 678.2923) 
(list 2634.585 678.4423) 
(list 2634.585 678.6193) 
(list 2560.5625 678.3693)))
(apply 'command (append '("pline") coords '("c")))
(setq currobj (ssadd (entlast) currobj))
(setq coords (list 
(list 2560.5625 678.5123) 
(list 2634.585 678.7623) 
(list 2634.585 678.9393) 
(list 2560.5625 678.5893)))
(apply 'command (append '("pline") coords '("c")))
(setq currobj (ssadd (entlast) currobj))
(setq coords (list 
(list 2560.5625 678.7323) 
(list 2634.585 679.0823) 
(list 2634.585 679.2593) 
(list 2560.5625 678.8093)))
(apply 'command (append '("pline") coords '("c")))
(setq currobj (ssadd (entlast) currobj))
(setq coords (list 
(list 2560.5625 678.9523) 
(list 2634.585 679.4023) 
(list 2634.585 679.5793) 
(list 2560.5625 679.0293)))
(apply 'command (append '("pline") coords '("c")))
(setq currobj (ssadd (entlast) currobj))
(setq coords (list 
(list 2560.5625 679.1723) 
(list 2634.585 679.7223) 
(list 2634.585 679.8993) 
(list 2560.5625 679.2493)))
(apply 'command (append '("pline") coords '("c")))
(setq currobj (ssadd (entlast) currobj))
(setq coords (list 
(list 2560.5625 679.3923) 
(list 2634.585 680.0423) 
(list 2634.585 680.2193) 
(list 2560.5625 679.4693)))
(apply 'command (append '("pline") coords '("c")))
(setq currobj (ssadd (entlast) currobj))
(setq coords (list 
(list 2559.4375 679.4693) 
(list 2485.415 680.2193) 
(list 2485.415 680.0423) 
(list 2559.4375 679.3923)))
(apply 'command (append '("pline") coords '("c")))
(setq currobj (ssadd (entlast) currobj))
(setq coords (list 
(list 2559.4375 679.2493) 
(list 2485.415 679.8993) 
(list 2485.415 679.7223) 
(list 2559.4375 679.1723)))
(apply 'command (append '("pline") coords '("c")))
(setq currobj (ssadd (entlast) currobj))
(setq coords (list 
(list 2559.4375 679.0293) 
(list 2485.415 679.5793) 
(list 2485.415 679.4023) 
(list 2559.4375 678.9523)))
(apply 'command (append '("pline") coords '("c")))
(setq currobj (ssadd (entlast) currobj))
(setq coords (list 
(list 2559.4375 678.8093) 
(list 2485.415 679.2593) 
(list 2485.415 679.0823) 
(list 2559.4375 678.7323)))
(apply 'command (append '("pline") coords '("c")))
(setq currobj (ssadd (entlast) currobj))
(setq coords (list 
(list 2559.4375 678.5893) 
(list 2485.415 678.9393) 
(list 2485.415 678.7623) 
(list 2559.4375 678.5123)))
(apply 'command (append '("pline") coords '("c")))
(setq currobj (ssadd (entlast) currobj))
(setq coords (list 
(list 2559.4375 678.3693) 
(list 2485.415 678.6193) 
(list 2485.415 678.4423) 
(list 2559.4375 678.2923)))
(apply 'command (append '("pline") coords '("c")))
(setq currobj (ssadd (entlast) currobj))
(setq coords (list 
(list 2559.4375 678.1493) 
(list 2485.415 678.2993) 
(list 2485.415 678.1223) 
(list 2559.4375 678.0723)))
(apply 'command (append '("pline") coords '("c")))
(setq currobj (ssadd (entlast) currobj))
(setq coords (list 
(list 2559.4375 677.9293) 
(list 2485.415 677.9793) 
(list 2485.415 677.8023) 
(list 2559.4375 677.8523)))
(apply 'command (append '("pline") coords '("c")))
(setq currobj (ssadd (entlast) currobj))
(setq coords (list 
(list 2559.4375 677.7093) 
(list 2485.415 677.6593) 
(list 2485.415 677.4823) 
(list 2559.4375 677.6323)))
(apply 'command (append '("pline") coords '("c")))
(setq currobj (ssadd (entlast) currobj))
(setq coords (list 
(list 2559.4375 677.4893) 
(list 2485.415 677.3393) 
(list 2485.415 677.1623) 
(list 2559.4375 677.4123)))
(apply 'command (append '("pline") coords '("c")))
(setq currobj (ssadd (entlast) currobj))
(setq coords (list 
(list 2559.4375 677.2693) 
(list 2485.415 677.0193) 
(list 2485.415 676.8423) 
(list 2559.4375 677.1923)))
(apply 'command (append '("pline") coords '("c")))
(setq currobj (ssadd (entlast) currobj))
(setq coords (list 
(list 2559.4375 677.0493) 
(list 2485.415 676.6993) 
(list 2485.415 676.5223) 
(list 2559.4375 676.9723)))
(apply 'command (append '("pline") coords '("c")))
(setq currobj (ssadd (entlast) currobj))
(setq coords (list 
(list 2559.4375 676.8293) 
(list 2485.415 676.3793) 
(list 2485.415 676.2023) 
(list 2559.4375 676.7523)))
(apply 'command (append '("pline") coords '("c")))
(setq currobj (ssadd (entlast) currobj))
(setq coords (list 
(list 2559.4375 676.6093) 
(list 2485.415 676.0593) 
(list 2485.415 675.8823) 
(list 2559.4375 676.5323)))
(apply 'command (append '("pline") coords '("c")))
(setq currobj (ssadd (entlast) currobj))
(setq coords (list 
(list 2559.4375 676.3893) 
(list 2485.415 675.7393) 
(list 2485.415 675.5623) 
(list 2559.4375 676.3123)))
(apply 'command (append '("pline") coords '("c")))
(setq currobj (ssadd (entlast) currobj))
(command "_layer" "set" "nitride" "")
(command "_layer" "set" "text" "")
(command "_circle" "2559.0625,665.1693" "0.075")
(command "_circle" "2559.0625,665.4693" "0.075")
(command "_circle" "2559.0625,665.7693" "0.075")
(command "_circle" "2559.0625,666.0693" "0.075")
(command "_circle" "2559.0625,666.3693" "0.075")
(command "_circle" "2558.7625,665.1693" "0.075")
(command "_circle" "2558.7625,665.4693" "0.075")
(command "_circle" "2558.7625,665.7693" "0.075")
(command "_circle" "2558.7625,666.0693" "0.075")
(command "_circle" "2558.7625,666.3693" "0.075")
(command "_circle" "2558.4625,665.1693" "0.075")
(command "_circle" "2558.4625,665.4693" "0.075")
(command "_circle" "2558.4625,665.7693" "0.075")
(command "_circle" "2558.4625,666.0693" "0.075")
(command "_circle" "2558.4625,666.3693" "0.075")
(command "_circle" "2558.1625,665.1693" "0.075")
(command "_circle" "2558.1625,665.4693" "0.075")
(command "_circle" "2558.1625,665.7693" "0.075")
(command "_circle" "2558.1625,666.0693" "0.075")
(command "_circle" "2558.1625,666.3693" "0.075")
(command "_circle" "2557.8625,665.1693" "0.075")
(command "_circle" "2557.8625,665.4693" "0.075")
(command "_circle" "2557.8625,665.7693" "0.075")
(command "_circle" "2557.8625,666.0693" "0.075")
(command "_circle" "2557.8625,666.3693" "0.075")
(command "_layer" "set" "nitride" "")
(setq coords (list 
(list 2560.2625 690.6123) 
(list 2560.2625 806.257) 
(list 2559.7375 806.257) 
(list 2559.7375 690.6123)))
(apply 'command (append '("pline") coords '("c")))
(setq currobj (ssadd (entlast) currobj))
(command "_layer" "set" "prebias" "")
(command "_rectangle" "2559.7375,690.6123" "2560.2625,806.257")
(setq currobj (ssadd (entlast) currobj))
(command "_layer" "set" "nitride" "")
(setq coords (list 
(list 2560.2625 806.257) 
(list 2560.5625 816.257) 
(list 2560.5625 816.257) 
(list 2560.5625 817.257) 
(list 2634.585 816.507) 
(list 2634.585 821.45) 
(list 2560.5625 820.7) 
(list 2560.5625 821.7) 
(list 2560.5625 821.7) 
(list 2560.2625 831.7) 
(list 2559.7375 831.7) 
(list 2559.4375 821.7) 
(list 2559.4375 821.7) 
(list 2559.4375 820.7) 
(list 2485.415 821.45) 
(list 2485.415 816.507) 
(list 2559.4375 817.257) 
(list 2559.4375 816.257) 
(list 2559.4375 816.257) 
(list 2559.7375 806.257)))
(apply 'command (append '("pline") coords '("c")))
(setq currobj (ssadd (entlast) currobj))
(command "_layer" "set" "prebias" "")
(setq coords (list 
(list 2559.4375 806.257) 
(list 2559.4375 817.257) 
(list 2485.415 816.507) 
(list 2485.415 821.45) 
(list 2559.4375 820.7) 
(list 2559.4375 831.7) 
(list 2560.5625 831.7) 
(list 2560.5625 820.7) 
(list 2634.585 821.45) 
(list 2634.585 816.507) 
(list 2560.5625 817.257) 
(list 2560.5625 806.257)))
(apply 'command (append '("pline") coords '("c")))
(setq currobj (ssadd (entlast) currobj))
(command "_layer" "set" "nitride" "")
(command "_layer" "set" "fda1" "")
(setq coords (list 
(list 2560.5625 817.4) 
(list 2634.585 816.65) 
(list 2634.585 816.827) 
(list 2560.5625 817.477)))
(apply 'command (append '("pline") coords '("c")))
(setq currobj (ssadd (entlast) currobj))
(setq coords (list 
(list 2560.5625 817.62) 
(list 2634.585 816.97) 
(list 2634.585 817.147) 
(list 2560.5625 817.697)))
(apply 'command (append '("pline") coords '("c")))
(setq currobj (ssadd (entlast) currobj))
(setq coords (list 
(list 2560.5625 817.84) 
(list 2634.585 817.29) 
(list 2634.585 817.467) 
(list 2560.5625 817.917)))
(apply 'command (append '("pline") coords '("c")))
(setq currobj (ssadd (entlast) currobj))
(setq coords (list 
(list 2560.5625 818.06) 
(list 2634.585 817.61) 
(list 2634.585 817.787) 
(list 2560.5625 818.137)))
(apply 'command (append '("pline") coords '("c")))
(setq currobj (ssadd (entlast) currobj))
(setq coords (list 
(list 2560.5625 818.28) 
(list 2634.585 817.93) 
(list 2634.585 818.107) 
(list 2560.5625 818.357)))
(apply 'command (append '("pline") coords '("c")))
(setq currobj (ssadd (entlast) currobj))
(setq coords (list 
(list 2560.5625 818.5) 
(list 2634.585 818.25) 
(list 2634.585 818.427) 
(list 2560.5625 818.577)))
(apply 'command (append '("pline") coords '("c")))
(setq currobj (ssadd (entlast) currobj))
(setq coords (list 
(list 2560.5625 818.72) 
(list 2634.585 818.57) 
(list 2634.585 818.747) 
(list 2560.5625 818.797)))
(apply 'command (append '("pline") coords '("c")))
(setq currobj (ssadd (entlast) currobj))
(setq coords (list 
(list 2560.5625 818.94) 
(list 2634.585 818.89) 
(list 2634.585 819.067) 
(list 2560.5625 819.017)))
(apply 'command (append '("pline") coords '("c")))
(setq currobj (ssadd (entlast) currobj))
(setq coords (list 
(list 2560.5625 819.16) 
(list 2634.585 819.21) 
(list 2634.585 819.387) 
(list 2560.5625 819.237)))
(apply 'command (append '("pline") coords '("c")))
(setq currobj (ssadd (entlast) currobj))
(setq coords (list 
(list 2560.5625 819.38) 
(list 2634.585 819.53) 
(list 2634.585 819.707) 
(list 2560.5625 819.457)))
(apply 'command (append '("pline") coords '("c")))
(setq currobj (ssadd (entlast) currobj))
(setq coords (list 
(list 2560.5625 819.6) 
(list 2634.585 819.85) 
(list 2634.585 820.027) 
(list 2560.5625 819.677)))
(apply 'command (append '("pline") coords '("c")))
(setq currobj (ssadd (entlast) currobj))
(setq coords (list 
(list 2560.5625 819.82) 
(list 2634.585 820.17) 
(list 2634.585 820.347) 
(list 2560.5625 819.897)))
(apply 'command (append '("pline") coords '("c")))
(setq currobj (ssadd (entlast) currobj))
(setq coords (list 
(list 2560.5625 820.04) 
(list 2634.585 820.49) 
(list 2634.585 820.667) 
(list 2560.5625 820.117)))
(apply 'command (append '("pline") coords '("c")))
(setq currobj (ssadd (entlast) currobj))
(setq coords (list 
(list 2560.5625 820.26) 
(list 2634.585 820.81) 
(list 2634.585 820.987) 
(list 2560.5625 820.337)))
(apply 'command (append '("pline") coords '("c")))
(setq currobj (ssadd (entlast) currobj))
(setq coords (list 
(list 2560.5625 820.48) 
(list 2634.585 821.13) 
(list 2634.585 821.307) 
(list 2560.5625 820.557)))
(apply 'command (append '("pline") coords '("c")))
(setq currobj (ssadd (entlast) currobj))
(setq coords (list 
(list 2559.4375 820.557) 
(list 2485.415 821.307) 
(list 2485.415 821.13) 
(list 2559.4375 820.48)))
(apply 'command (append '("pline") coords '("c")))
(setq currobj (ssadd (entlast) currobj))
(setq coords (list 
(list 2559.4375 820.337) 
(list 2485.415 820.987) 
(list 2485.415 820.81) 
(list 2559.4375 820.26)))
(apply 'command (append '("pline") coords '("c")))
(setq currobj (ssadd (entlast) currobj))
(setq coords (list 
(list 2559.4375 820.117) 
(list 2485.415 820.667) 
(list 2485.415 820.49) 
(list 2559.4375 820.04)))
(apply 'command (append '("pline") coords '("c")))
(setq currobj (ssadd (entlast) currobj))
(setq coords (list 
(list 2559.4375 819.897) 
(list 2485.415 820.347) 
(list 2485.415 820.17) 
(list 2559.4375 819.82)))
(apply 'command (append '("pline") coords '("c")))
(setq currobj (ssadd (entlast) currobj))
(setq coords (list 
(list 2559.4375 819.677) 
(list 2485.415 820.027) 
(list 2485.415 819.85) 
(list 2559.4375 819.6)))
(apply 'command (append '("pline") coords '("c")))
(setq currobj (ssadd (entlast) currobj))
(setq coords (list 
(list 2559.4375 819.457) 
(list 2485.415 819.707) 
(list 2485.415 819.53) 
(list 2559.4375 819.38)))
(apply 'command (append '("pline") coords '("c")))
(setq currobj (ssadd (entlast) currobj))
(setq coords (list 
(list 2559.4375 819.237) 
(list 2485.415 819.387) 
(list 2485.415 819.21) 
(list 2559.4375 819.16)))
(apply 'command (append '("pline") coords '("c")))
(setq currobj (ssadd (entlast) currobj))
(setq coords (list 
(list 2559.4375 819.017) 
(list 2485.415 819.067) 
(list 2485.415 818.89) 
(list 2559.4375 818.94)))
(apply 'command (append '("pline") coords '("c")))
(setq currobj (ssadd (entlast) currobj))
(setq coords (list 
(list 2559.4375 818.797) 
(list 2485.415 818.747) 
(list 2485.415 818.57) 
(list 2559.4375 818.72)))
(apply 'command (append '("pline") coords '("c")))
(setq currobj (ssadd (entlast) currobj))
(setq coords (list 
(list 2559.4375 818.577) 
(list 2485.415 818.427) 
(list 2485.415 818.25) 
(list 2559.4375 818.5)))
(apply 'command (append '("pline") coords '("c")))
(setq currobj (ssadd (entlast) currobj))
(setq coords (list 
(list 2559.4375 818.357) 
(list 2485.415 818.107) 
(list 2485.415 817.93) 
(list 2559.4375 818.28)))
(apply 'command (append '("pline") coords '("c")))
(setq currobj (ssadd (entlast) currobj))
(setq coords (list 
(list 2559.4375 818.137) 
(list 2485.415 817.787) 
(list 2485.415 817.61) 
(list 2559.4375 818.06)))
(apply 'command (append '("pline") coords '("c")))
(setq currobj (ssadd (entlast) currobj))
(setq coords (list 
(list 2559.4375 817.917) 
(list 2485.415 817.467) 
(list 2485.415 817.29) 
(list 2559.4375 817.84)))
(apply 'command (append '("pline") coords '("c")))
(setq currobj (ssadd (entlast) currobj))
(setq coords (list 
(list 2559.4375 817.697) 
(list 2485.415 817.147) 
(list 2485.415 816.97) 
(list 2559.4375 817.62)))
(apply 'command (append '("pline") coords '("c")))
(setq currobj (ssadd (entlast) currobj))
(setq coords (list 
(list 2559.4375 817.477) 
(list 2485.415 816.827) 
(list 2485.415 816.65) 
(list 2559.4375 817.4)))
(apply 'command (append '("pline") coords '("c")))
(setq currobj (ssadd (entlast) currobj))
(command "_layer" "set" "nitride" "")
(command "_layer" "set" "text" "")
(command "_circle" "2559.0625,806.257" "0.075")
(command "_circle" "2559.0625,806.557" "0.075")
(command "_circle" "2559.0625,806.857" "0.075")
(command "_circle" "2559.0625,807.157" "0.075")
(command "_circle" "2559.0625,807.457" "0.075")
(command "_circle" "2558.7625,806.257" "0.075")
(command "_circle" "2558.7625,806.557" "0.075")
(command "_circle" "2558.7625,806.857" "0.075")
(command "_circle" "2558.7625,807.157" "0.075")
(command "_circle" "2558.7625,807.457" "0.075")
(command "_circle" "2558.4625,806.257" "0.075")
(command "_circle" "2558.4625,806.557" "0.075")
(command "_circle" "2558.4625,806.857" "0.075")
(command "_circle" "2558.4625,807.157" "0.075")
(command "_circle" "2558.4625,807.457" "0.075")
(command "_circle" "2558.1625,806.257" "0.075")
(command "_circle" "2558.1625,806.557" "0.075")
(command "_circle" "2558.1625,806.857" "0.075")
(command "_circle" "2558.1625,807.157" "0.075")
(command "_circle" "2558.1625,807.457" "0.075")
(command "_circle" "2557.8625,806.257" "0.075")
(command "_circle" "2557.8625,806.557" "0.075")
(command "_circle" "2557.8625,806.857" "0.075")
(command "_circle" "2557.8625,807.157" "0.075")
(command "_circle" "2557.8625,807.457" "0.075")
(command "_layer" "set" "nitride" "")
(setq coords (list 
(list 2560.2625 831.7) 
(list 2560.2625 836.7) 
(list 2559.7375 836.7) 
(list 2559.7375 831.7)))
(apply 'command (append '("pline") coords '("c")))
(setq currobj (ssadd (entlast) currobj))
(command "_layer" "set" "prebias" "")
(command "_rectangle" "2559.7375,831.7" "2560.2625,836.7")
(setq currobj (ssadd (entlast) currobj))
(command "_layer" "set" "nitride" "")
(setq cooledsinglenanobeam8 currobj)
(setq currobj nil)
(setq currobj (ssadd))
; DRAWING PHOTONIC CRYSTAL
(command "_layer" "set" "negYjunc" "")
(setq coords (list 
(list 2560.135 866.7) 
(list 2560 851.7) 
(list 2560 866.7)))
(apply 'command (append '("pline") coords '("c")))
(setq currobj (ssadd (entlast) currobj))
(setq coords (list 
(list 2560.2625 836.7) 
(list 2560.415 866.7) 
(list 2561.106 866.7) 
(list 2561.106 836.7)))
(apply 'command (append '("pline") coords '("c")))
(setq currobj (ssadd (entlast) currobj))
(setq coords (list 
(list 2559.865 866.7) 
(list 2560 851.7) 
(list 2560 866.7)))
(apply 'command (append '("pline") coords '("c")))
(setq currobj (ssadd (entlast) currobj))
(setq coords (list 
(list 2559.7375 836.7) 
(list 2559.585 866.7) 
(list 2558.894 866.7) 
(list 2558.894 836.7)))
(apply 'command (append '("pline") coords '("c")))
(setq currobj (ssadd (entlast) currobj))
(command "_layer" "set" "nitride" "")
(setq yjunction8 currobj)
(setq currobj nil)
(setq currobj (ssadd))
(setq tap8 nil)
(setq tap8 (ssadd))
(command "_layer" "set" "phc" "")
(setq coords (list 
(list 2560 866.7) 
(list 2560.135 866.7) 
(list 2560.135 866.7103) 
(list 2560.135 866.7206) 
(list 2560.135 866.7308) 
(list 2560.135 866.7411) 
(list 2560.135 866.7514) 
(list 2560.135 866.7617) 
(list 2560.135 866.7719) 
(list 2560.135 866.7822) 
(list 2560.135 866.7925) 
(list 2560.135 866.8028) 
(list 2560.135 866.8131) 
(list 2560.135 866.8233) 
(list 2560.135 866.8336) 
(list 2560.135 866.8439) 
(list 2560.135 866.8542) 
(list 2560.135 866.8644) 
(list 2560.135 866.8747) 
(list 2560.135 866.885) 
(list 2560.135 866.8953) 
(list 2560.135 866.9056) 
(list 2560.135 866.9158) 
(list 2560.135 866.9261) 
(list 2560.135 866.9364) 
(list 2560.135 866.9467) 
(list 2560.135 866.9569) 
(list 2560.135 866.9672) 
(list 2560.135 866.9775) 
(list 2560.135 866.9878) 
(list 2560.135 866.9981) 
(list 2560.135 867.0083) 
(list 2560.135 867.0186) 
(list 2560.135 867.0289) 
(list 2560.135 867.0392) 
(list 2560.135 867.0494) 
(list 2560.135 867.0597) 
(list 2560.135 867.07) 
(list 2560 867.07)))
(apply 'command (append '("pline") coords '("c")))
(setq tap8 (ssadd (entlast) tap8))
(command "_mirror" (entlast) "" "2560,900" "2560,901" "No")
(setq tap8 (ssadd (entlast) tap8))
(setq coords (list 
(list 2560.4242 866.7) 
(list 2560.415 866.7) 
(list 2560.4153 866.7103) 
(list 2560.4155 866.7206) 
(list 2560.4157 866.7308) 
(list 2560.4158 866.7411) 
(list 2560.4158 866.7514) 
(list 2560.4158 866.7617) 
(list 2560.4156 866.7719) 
(list 2560.4154 866.7822) 
(list 2560.415 866.7925) 
(list 2560.4146 866.8028) 
(list 2560.4141 866.8131) 
(list 2560.4135 866.8233) 
(list 2560.4129 866.8336) 
(list 2560.4123 866.8439) 
(list 2560.4117 866.8542) 
(list 2560.4112 866.8644) 
(list 2560.4108 866.8747) 
(list 2560.4105 866.885) 
(list 2560.4103 866.8953) 
(list 2560.4103 866.9056) 
(list 2560.4104 866.9158) 
(list 2560.4108 866.9261) 
(list 2560.4113 866.9364) 
(list 2560.412 866.9467) 
(list 2560.4129 866.9569) 
(list 2560.4139 866.9672) 
(list 2560.4151 866.9775) 
(list 2560.4163 866.9878) 
(list 2560.4176 866.9981) 
(list 2560.4189 867.0083) 
(list 2560.4201 867.0186) 
(list 2560.4213 867.0289) 
(list 2560.4223 867.0392) 
(list 2560.4232 867.0494) 
(list 2560.4238 867.0597) 
(list 2560.4242 867.07) 
(list 2560.4242 867.07)))
(apply 'command (append '("pline") coords '("c")))
(setq tap8 (ssadd (entlast) tap8))
(command "_mirror" (entlast) "" "2560,900" "2560,901" "No")
(setq tap8 (ssadd (entlast) tap8))
(setq coords (list 
(list 2561.106 866.7) 
(list 2560.4242 866.7) 
(list 2560.4242 866.7103) 
(list 2560.4242 866.7206) 
(list 2560.4242 866.7308) 
(list 2560.4242 866.7411) 
(list 2560.4242 866.7514) 
(list 2560.4242 866.7617) 
(list 2560.4242 866.7719) 
(list 2560.4242 866.7822) 
(list 2560.4242 866.7925) 
(list 2560.4242 866.8028) 
(list 2560.4242 866.8131) 
(list 2560.4242 866.8233) 
(list 2560.4242 866.8336) 
(list 2560.4242 866.8439) 
(list 2560.4242 866.8542) 
(list 2560.4242 866.8644) 
(list 2560.4242 866.8747) 
(list 2560.4242 866.885) 
(list 2560.4242 866.8953) 
(list 2560.4242 866.9056) 
(list 2560.4242 866.9158) 
(list 2560.4242 866.9261) 
(list 2560.4242 866.9364) 
(list 2560.4242 866.9467) 
(list 2560.4242 866.9569) 
(list 2560.4242 866.9672) 
(list 2560.4242 866.9775) 
(list 2560.4242 866.9878) 
(list 2560.4242 866.9981) 
(list 2560.4242 867.0083) 
(list 2560.4242 867.0186) 
(list 2560.4242 867.0289) 
(list 2560.4242 867.0392) 
(list 2560.4242 867.0494) 
(list 2560.4242 867.0597) 
(list 2560.4242 867.07) 
(list 2561.106 867.07)))
(apply 'command (append '("pline") coords '("c")))
(setq tap8 (ssadd (entlast) tap8))
(command "_mirror" (entlast) "" "2560,900" "2560,901" "No")
(setq tap8 (ssadd (entlast) tap8))
(setq coords (list 
(list 2560 867.07) 
(list 2560.135 867.07) 
(list 2560.135 867.0803) 
(list 2560.135 867.0906) 
(list 2560.135 867.1008) 
(list 2560.135 867.1111) 
(list 2560.135 867.1214) 
(list 2560.135 867.1317) 
(list 2560.135 867.1419) 
(list 2560.135 867.1522) 
(list 2560.135 867.1625) 
(list 2560.135 867.1728) 
(list 2560.135 867.1831) 
(list 2560.135 867.1933) 
(list 2560.135 867.2036) 
(list 2560.135 867.2139) 
(list 2560.135 867.2242) 
(list 2560.135 867.2344) 
(list 2560.135 867.2447) 
(list 2560.135 867.255) 
(list 2560.135 867.2653) 
(list 2560.135 867.2756) 
(list 2560.135 867.2858) 
(list 2560.135 867.2961) 
(list 2560.135 867.3064) 
(list 2560.135 867.3167) 
(list 2560.135 867.3269) 
(list 2560.135 867.3372) 
(list 2560.135 867.3475) 
(list 2560.135 867.3578) 
(list 2560.135 867.3681) 
(list 2560.135 867.3783) 
(list 2560.135 867.3886) 
(list 2560.135 867.3989) 
(list 2560.135 867.4092) 
(list 2560.135 867.4194) 
(list 2560.135 867.4297) 
(list 2560.135 867.44) 
(list 2560 867.44)))
(apply 'command (append '("pline") coords '("c")))
(setq tap8 (ssadd (entlast) tap8))
(command "_mirror" (entlast) "" "2560,900" "2560,901" "No")
(setq tap8 (ssadd (entlast) tap8))
(setq coords (list 
(list 2560.4334 867.07) 
(list 2560.4242 867.07) 
(list 2560.4243 867.0803) 
(list 2560.4241 867.0906) 
(list 2560.4236 867.1008) 
(list 2560.4228 867.1111) 
(list 2560.4218 867.1214) 
(list 2560.4204 867.1317) 
(list 2560.4188 867.1419) 
(list 2560.417 867.1522) 
(list 2560.4151 867.1625) 
(list 2560.4131 867.1728) 
(list 2560.411 867.1831) 
(list 2560.409 867.1933) 
(list 2560.4071 867.2036) 
(list 2560.4054 867.2139) 
(list 2560.4039 867.2242) 
(list 2560.4027 867.2344) 
(list 2560.4019 867.2447) 
(list 2560.4014 867.255) 
(list 2560.4014 867.2653) 
(list 2560.4018 867.2756) 
(list 2560.4026 867.2858) 
(list 2560.4038 867.2961) 
(list 2560.4055 867.3064) 
(list 2560.4075 867.3167) 
(list 2560.4098 867.3269) 
(list 2560.4124 867.3372) 
(list 2560.4151 867.3475) 
(list 2560.4179 867.3578) 
(list 2560.4208 867.3681) 
(list 2560.4235 867.3783) 
(list 2560.4261 867.3886) 
(list 2560.4283 867.3989) 
(list 2560.4303 867.4092) 
(list 2560.4318 867.4194) 
(list 2560.4329 867.4297) 
(list 2560.4334 867.44) 
(list 2560.4334 867.44)))
(apply 'command (append '("pline") coords '("c")))
(setq tap8 (ssadd (entlast) tap8))
(command "_mirror" (entlast) "" "2560,900" "2560,901" "No")
(setq tap8 (ssadd (entlast) tap8))
(setq coords (list 
(list 2561.106 867.07) 
(list 2560.4334 867.07) 
(list 2560.4334 867.0803) 
(list 2560.4334 867.0906) 
(list 2560.4334 867.1008) 
(list 2560.4334 867.1111) 
(list 2560.4334 867.1214) 
(list 2560.4334 867.1317) 
(list 2560.4334 867.1419) 
(list 2560.4334 867.1522) 
(list 2560.4334 867.1625) 
(list 2560.4334 867.1728) 
(list 2560.4334 867.1831) 
(list 2560.4334 867.1933) 
(list 2560.4334 867.2036) 
(list 2560.4334 867.2139) 
(list 2560.4334 867.2242) 
(list 2560.4334 867.2344) 
(list 2560.4334 867.2447) 
(list 2560.4334 867.255) 
(list 2560.4334 867.2653) 
(list 2560.4334 867.2756) 
(list 2560.4334 867.2858) 
(list 2560.4334 867.2961) 
(list 2560.4334 867.3064) 
(list 2560.4334 867.3167) 
(list 2560.4334 867.3269) 
(list 2560.4334 867.3372) 
(list 2560.4334 867.3475) 
(list 2560.4334 867.3578) 
(list 2560.4334 867.3681) 
(list 2560.4334 867.3783) 
(list 2560.4334 867.3886) 
(list 2560.4334 867.3989) 
(list 2560.4334 867.4092) 
(list 2560.4334 867.4194) 
(list 2560.4334 867.4297) 
(list 2560.4334 867.44) 
(list 2561.106 867.44)))
(apply 'command (append '("pline") coords '("c")))
(setq tap8 (ssadd (entlast) tap8))
(command "_mirror" (entlast) "" "2560,900" "2560,901" "No")
(setq tap8 (ssadd (entlast) tap8))
(setq coords (list 
(list 2560 867.44) 
(list 2560.135 867.44) 
(list 2560.135 867.4503) 
(list 2560.135 867.4606) 
(list 2560.135 867.4708) 
(list 2560.135 867.4811) 
(list 2560.135 867.4914) 
(list 2560.135 867.5017) 
(list 2560.135 867.5119) 
(list 2560.135 867.5222) 
(list 2560.135 867.5325) 
(list 2560.135 867.5428) 
(list 2560.135 867.5531) 
(list 2560.135 867.5633) 
(list 2560.135 867.5736) 
(list 2560.135 867.5839) 
(list 2560.135 867.5942) 
(list 2560.135 867.6044) 
(list 2560.135 867.6147) 
(list 2560.135 867.625) 
(list 2560.135 867.6353) 
(list 2560.135 867.6456) 
(list 2560.135 867.6558) 
(list 2560.135 867.6661) 
(list 2560.135 867.6764) 
(list 2560.135 867.6867) 
(list 2560.135 867.6969) 
(list 2560.135 867.7072) 
(list 2560.135 867.7175) 
(list 2560.135 867.7278) 
(list 2560.135 867.7381) 
(list 2560.135 867.7483) 
(list 2560.135 867.7586) 
(list 2560.135 867.7689) 
(list 2560.135 867.7792) 
(list 2560.135 867.7894) 
(list 2560.135 867.7997) 
(list 2560.135 867.81) 
(list 2560 867.81)))
(apply 'command (append '("pline") coords '("c")))
(setq tap8 (ssadd (entlast) tap8))
(command "_mirror" (entlast) "" "2560,900" "2560,901" "No")
(setq tap8 (ssadd (entlast) tap8))
(setq coords (list 
(list 2560.4426 867.44) 
(list 2560.4334 867.44) 
(list 2560.4334 867.4503) 
(list 2560.4328 867.4606) 
(list 2560.4316 867.4708) 
(list 2560.4299 867.4811) 
(list 2560.4277 867.4914) 
(list 2560.425 867.5017) 
(list 2560.422 867.5119) 
(list 2560.4187 867.5222) 
(list 2560.4151 867.5325) 
(list 2560.4115 867.5428) 
(list 2560.408 867.5531) 
(list 2560.4045 867.5633) 
(list 2560.4013 867.5736) 
(list 2560.3984 867.5839) 
(list 2560.396 867.5942) 
(list 2560.3942 867.6044) 
(list 2560.3929 867.6147) 
(list 2560.3923 867.625) 
(list 2560.3924 867.6353) 
(list 2560.3932 867.6456) 
(list 2560.3947 867.6558) 
(list 2560.3969 867.6661) 
(list 2560.3997 867.6764) 
(list 2560.403 867.6867) 
(list 2560.4068 867.6969) 
(list 2560.4109 867.7072) 
(list 2560.4152 867.7175) 
(list 2560.4196 867.7278) 
(list 2560.424 867.7381) 
(list 2560.4281 867.7483) 
(list 2560.432 867.7586) 
(list 2560.4354 867.7689) 
(list 2560.4383 867.7792) 
(list 2560.4405 867.7894) 
(list 2560.4419 867.7997) 
(list 2560.4426 867.81) 
(list 2560.4426 867.81)))
(apply 'command (append '("pline") coords '("c")))
(setq tap8 (ssadd (entlast) tap8))
(command "_mirror" (entlast) "" "2560,900" "2560,901" "No")
(setq tap8 (ssadd (entlast) tap8))
(setq coords (list 
(list 2561.106 867.44) 
(list 2560.4426 867.44) 
(list 2560.4426 867.4503) 
(list 2560.4426 867.4606) 
(list 2560.4426 867.4708) 
(list 2560.4426 867.4811) 
(list 2560.4426 867.4914) 
(list 2560.4426 867.5017) 
(list 2560.4426 867.5119) 
(list 2560.4426 867.5222) 
(list 2560.4426 867.5325) 
(list 2560.4426 867.5428) 
(list 2560.4426 867.5531) 
(list 2560.4426 867.5633) 
(list 2560.4426 867.5736) 
(list 2560.4426 867.5839) 
(list 2560.4426 867.5942) 
(list 2560.4426 867.6044) 
(list 2560.4426 867.6147) 
(list 2560.4426 867.625) 
(list 2560.4426 867.6353) 
(list 2560.4426 867.6456) 
(list 2560.4426 867.6558) 
(list 2560.4426 867.6661) 
(list 2560.4426 867.6764) 
(list 2560.4426 867.6867) 
(list 2560.4426 867.6969) 
(list 2560.4426 867.7072) 
(list 2560.4426 867.7175) 
(list 2560.4426 867.7278) 
(list 2560.4426 867.7381) 
(list 2560.4426 867.7483) 
(list 2560.4426 867.7586) 
(list 2560.4426 867.7689) 
(list 2560.4426 867.7792) 
(list 2560.4426 867.7894) 
(list 2560.4426 867.7997) 
(list 2560.4426 867.81) 
(list 2561.106 867.81)))
(apply 'command (append '("pline") coords '("c")))
(setq tap8 (ssadd (entlast) tap8))
(command "_mirror" (entlast) "" "2560,900" "2560,901" "No")
(setq tap8 (ssadd (entlast) tap8))
(setq coords (list 
(list 2560 867.81) 
(list 2560.135 867.81) 
(list 2560.135 867.8203) 
(list 2560.135 867.8306) 
(list 2560.135 867.8408) 
(list 2560.135 867.8511) 
(list 2560.135 867.8614) 
(list 2560.135 867.8717) 
(list 2560.135 867.8819) 
(list 2560.135 867.8922) 
(list 2560.135 867.9025) 
(list 2560.135 867.9128) 
(list 2560.135 867.9231) 
(list 2560.135 867.9333) 
(list 2560.135 867.9436) 
(list 2560.135 867.9539) 
(list 2560.135 867.9642) 
(list 2560.135 867.9744) 
(list 2560.135 867.9847) 
(list 2560.135 867.995) 
(list 2560.135 868.0053) 
(list 2560.135 868.0156) 
(list 2560.135 868.0258) 
(list 2560.135 868.0361) 
(list 2560.135 868.0464) 
(list 2560.135 868.0567) 
(list 2560.135 868.0669) 
(list 2560.135 868.0772) 
(list 2560.135 868.0875) 
(list 2560.135 868.0978) 
(list 2560.135 868.1081) 
(list 2560.135 868.1183) 
(list 2560.135 868.1286) 
(list 2560.135 868.1389) 
(list 2560.135 868.1492) 
(list 2560.135 868.1594) 
(list 2560.135 868.1697) 
(list 2560.135 868.18) 
(list 2560 868.18)))
(apply 'command (append '("pline") coords '("c")))
(setq tap8 (ssadd (entlast) tap8))
(command "_mirror" (entlast) "" "2560,900" "2560,901" "No")
(setq tap8 (ssadd (entlast) tap8))
(setq coords (list 
(list 2560.4518 867.81) 
(list 2560.4426 867.81) 
(list 2560.4424 867.8203) 
(list 2560.4414 867.8306) 
(list 2560.4396 867.8408) 
(list 2560.437 867.8511) 
(list 2560.4336 867.8614) 
(list 2560.4297 867.8717) 
(list 2560.4252 867.8819) 
(list 2560.4203 867.8922) 
(list 2560.4152 867.9025) 
(list 2560.41 867.9128) 
(list 2560.4049 867.9231) 
(list 2560.4 867.9333) 
(list 2560.3955 867.9436) 
(list 2560.3915 867.9539) 
(list 2560.3882 867.9642) 
(list 2560.3857 867.9744) 
(list 2560.384 867.9847) 
(list 2560.3833 867.995) 
(list 2560.3835 868.0053) 
(list 2560.3847 868.0156) 
(list 2560.3869 868.0258) 
(list 2560.39 868.0361) 
(list 2560.3939 868.0464) 
(list 2560.3985 868.0567) 
(list 2560.4037 868.0669) 
(list 2560.4093 868.0772) 
(list 2560.4153 868.0875) 
(list 2560.4212 868.0978) 
(list 2560.4271 868.1081) 
(list 2560.4328 868.1183) 
(list 2560.4379 868.1286) 
(list 2560.4425 868.1389) 
(list 2560.4462 868.1492) 
(list 2560.4491 868.1594) 
(list 2560.451 868.1697) 
(list 2560.4518 868.18) 
(list 2560.4518 868.18)))
(apply 'command (append '("pline") coords '("c")))
(setq tap8 (ssadd (entlast) tap8))
(command "_mirror" (entlast) "" "2560,900" "2560,901" "No")
(setq tap8 (ssadd (entlast) tap8))
(setq coords (list 
(list 2561.106 867.81) 
(list 2560.4518 867.81) 
(list 2560.4518 867.8203) 
(list 2560.4518 867.8306) 
(list 2560.4518 867.8408) 
(list 2560.4518 867.8511) 
(list 2560.4518 867.8614) 
(list 2560.4518 867.8717) 
(list 2560.4518 867.8819) 
(list 2560.4518 867.8922) 
(list 2560.4518 867.9025) 
(list 2560.4518 867.9128) 
(list 2560.4518 867.9231) 
(list 2560.4518 867.9333) 
(list 2560.4518 867.9436) 
(list 2560.4518 867.9539) 
(list 2560.4518 867.9642) 
(list 2560.4518 867.9744) 
(list 2560.4518 867.9847) 
(list 2560.4518 867.995) 
(list 2560.4518 868.0053) 
(list 2560.4518 868.0156) 
(list 2560.4518 868.0258) 
(list 2560.4518 868.0361) 
(list 2560.4518 868.0464) 
(list 2560.4518 868.0567) 
(list 2560.4518 868.0669) 
(list 2560.4518 868.0772) 
(list 2560.4518 868.0875) 
(list 2560.4518 868.0978) 
(list 2560.4518 868.1081) 
(list 2560.4518 868.1183) 
(list 2560.4518 868.1286) 
(list 2560.4518 868.1389) 
(list 2560.4518 868.1492) 
(list 2560.4518 868.1594) 
(list 2560.4518 868.1697) 
(list 2560.4518 868.18) 
(list 2561.106 868.18)))
(apply 'command (append '("pline") coords '("c")))
(setq tap8 (ssadd (entlast) tap8))
(command "_mirror" (entlast) "" "2560,900" "2560,901" "No")
(setq tap8 (ssadd (entlast) tap8))
(setq coords (list 
(list 2560 868.18) 
(list 2560.135 868.18) 
(list 2560.135 868.1903) 
(list 2560.135 868.2006) 
(list 2560.135 868.2108) 
(list 2560.135 868.2211) 
(list 2560.135 868.2314) 
(list 2560.135 868.2417) 
(list 2560.135 868.2519) 
(list 2560.135 868.2622) 
(list 2560.135 868.2725) 
(list 2560.135 868.2828) 
(list 2560.135 868.2931) 
(list 2560.135 868.3033) 
(list 2560.135 868.3136) 
(list 2560.135 868.3239) 
(list 2560.135 868.3342) 
(list 2560.135 868.3444) 
(list 2560.135 868.3547) 
(list 2560.135 868.365) 
(list 2560.135 868.3753) 
(list 2560.135 868.3856) 
(list 2560.135 868.3958) 
(list 2560.135 868.4061) 
(list 2560.135 868.4164) 
(list 2560.135 868.4267) 
(list 2560.135 868.4369) 
(list 2560.135 868.4472) 
(list 2560.135 868.4575) 
(list 2560.135 868.4678) 
(list 2560.135 868.4781) 
(list 2560.135 868.4883) 
(list 2560.135 868.4986) 
(list 2560.135 868.5089) 
(list 2560.135 868.5192) 
(list 2560.135 868.5294) 
(list 2560.135 868.5397) 
(list 2560.135 868.55) 
(list 2560 868.55)))
(apply 'command (append '("pline") coords '("c")))
(setq tap8 (ssadd (entlast) tap8))
(command "_mirror" (entlast) "" "2560,900" "2560,901" "No")
(setq tap8 (ssadd (entlast) tap8))
(setq coords (list 
(list 2560.461 868.18) 
(list 2560.4518 868.18) 
(list 2560.4515 868.1903) 
(list 2560.4501 868.2006) 
(list 2560.4476 868.2108) 
(list 2560.444 868.2211) 
(list 2560.4396 868.2314) 
(list 2560.4343 868.2417) 
(list 2560.4284 868.2519) 
(list 2560.422 868.2622) 
(list 2560.4153 868.2725) 
(list 2560.4085 868.2828) 
(list 2560.4018 868.2931) 
(list 2560.3955 868.3033) 
(list 2560.3897 868.3136) 
(list 2560.3846 868.3239) 
(list 2560.3804 868.3342) 
(list 2560.3772 868.3444) 
(list 2560.3751 868.3547) 
(list 2560.3742 868.365) 
(list 2560.3746 868.3753) 
(list 2560.3762 868.3856) 
(list 2560.3791 868.3958) 
(list 2560.383 868.4061) 
(list 2560.3881 868.4164) 
(list 2560.394 868.4267) 
(list 2560.4006 868.4369) 
(list 2560.4078 868.4472) 
(list 2560.4153 868.4575) 
(list 2560.4229 868.4678) 
(list 2560.4303 868.4781) 
(list 2560.4374 868.4883) 
(list 2560.4439 868.4986) 
(list 2560.4495 868.5089) 
(list 2560.4542 868.5192) 
(list 2560.4578 868.5294) 
(list 2560.4601 868.5397) 
(list 2560.461 868.55) 
(list 2560.461 868.55)))
(apply 'command (append '("pline") coords '("c")))
(setq tap8 (ssadd (entlast) tap8))
(command "_mirror" (entlast) "" "2560,900" "2560,901" "No")
(setq tap8 (ssadd (entlast) tap8))
(setq coords (list 
(list 2561.106 868.18) 
(list 2560.461 868.18) 
(list 2560.461 868.1903) 
(list 2560.461 868.2006) 
(list 2560.461 868.2108) 
(list 2560.461 868.2211) 
(list 2560.461 868.2314) 
(list 2560.461 868.2417) 
(list 2560.461 868.2519) 
(list 2560.461 868.2622) 
(list 2560.461 868.2725) 
(list 2560.461 868.2828) 
(list 2560.461 868.2931) 
(list 2560.461 868.3033) 
(list 2560.461 868.3136) 
(list 2560.461 868.3239) 
(list 2560.461 868.3342) 
(list 2560.461 868.3444) 
(list 2560.461 868.3547) 
(list 2560.461 868.365) 
(list 2560.461 868.3753) 
(list 2560.461 868.3856) 
(list 2560.461 868.3958) 
(list 2560.461 868.4061) 
(list 2560.461 868.4164) 
(list 2560.461 868.4267) 
(list 2560.461 868.4369) 
(list 2560.461 868.4472) 
(list 2560.461 868.4575) 
(list 2560.461 868.4678) 
(list 2560.461 868.4781) 
(list 2560.461 868.4883) 
(list 2560.461 868.4986) 
(list 2560.461 868.5089) 
(list 2560.461 868.5192) 
(list 2560.461 868.5294) 
(list 2560.461 868.5397) 
(list 2560.461 868.55) 
(list 2561.106 868.55)))
(apply 'command (append '("pline") coords '("c")))
(setq tap8 (ssadd (entlast) tap8))
(command "_mirror" (entlast) "" "2560,900" "2560,901" "No")
(setq tap8 (ssadd (entlast) tap8))
(setq coords (list 
(list 2560 868.55) 
(list 2560.135 868.55) 
(list 2560.135 868.5603) 
(list 2560.135 868.5706) 
(list 2560.135 868.5808) 
(list 2560.135 868.5911) 
(list 2560.135 868.6014) 
(list 2560.135 868.6117) 
(list 2560.135 868.6219) 
(list 2560.135 868.6322) 
(list 2560.135 868.6425) 
(list 2560.135 868.6528) 
(list 2560.135 868.6631) 
(list 2560.135 868.6733) 
(list 2560.135 868.6836) 
(list 2560.135 868.6939) 
(list 2560.135 868.7042) 
(list 2560.135 868.7144) 
(list 2560.135 868.7247) 
(list 2560.135 868.735) 
(list 2560.135 868.7453) 
(list 2560.135 868.7556) 
(list 2560.135 868.7658) 
(list 2560.135 868.7761) 
(list 2560.135 868.7864) 
(list 2560.135 868.7967) 
(list 2560.135 868.8069) 
(list 2560.135 868.8172) 
(list 2560.135 868.8275) 
(list 2560.135 868.8378) 
(list 2560.135 868.8481) 
(list 2560.135 868.8583) 
(list 2560.135 868.8686) 
(list 2560.135 868.8789) 
(list 2560.135 868.8892) 
(list 2560.135 868.8994) 
(list 2560.135 868.9097) 
(list 2560.135 868.92) 
(list 2560 868.92)))
(apply 'command (append '("pline") coords '("c")))
(setq tap8 (ssadd (entlast) tap8))
(command "_mirror" (entlast) "" "2560,900" "2560,901" "No")
(setq tap8 (ssadd (entlast) tap8))
(setq coords (list 
(list 2560.4702 868.55) 
(list 2560.461 868.55) 
(list 2560.4606 868.5603) 
(list 2560.4587 868.5706) 
(list 2560.4555 868.5808) 
(list 2560.4511 868.5911) 
(list 2560.4455 868.6014) 
(list 2560.4389 868.6117) 
(list 2560.4316 868.6219) 
(list 2560.4236 868.6322) 
(list 2560.4154 868.6425) 
(list 2560.407 868.6528) 
(list 2560.3988 868.6631) 
(list 2560.391 868.6733) 
(list 2560.3839 868.6836) 
(list 2560.3777 868.6939) 
(list 2560.3725 868.7042) 
(list 2560.3686 868.7144) 
(list 2560.3661 868.7247) 
(list 2560.3651 868.735) 
(list 2560.3656 868.7453) 
(list 2560.3677 868.7556) 
(list 2560.3712 868.7658) 
(list 2560.3761 868.7761) 
(list 2560.3823 868.7864) 
(list 2560.3895 868.7967) 
(list 2560.3976 868.8069) 
(list 2560.4063 868.8172) 
(list 2560.4154 868.8275) 
(list 2560.4245 868.8378) 
(list 2560.4335 868.8481) 
(list 2560.442 868.8583) 
(list 2560.4498 868.8686) 
(list 2560.4566 868.8789) 
(list 2560.4622 868.8892) 
(list 2560.4664 868.8994) 
(list 2560.4691 868.9097) 
(list 2560.4702 868.92) 
(list 2560.4702 868.92)))
(apply 'command (append '("pline") coords '("c")))
(setq tap8 (ssadd (entlast) tap8))
(command "_mirror" (entlast) "" "2560,900" "2560,901" "No")
(setq tap8 (ssadd (entlast) tap8))
(setq coords (list 
(list 2561.106 868.55) 
(list 2560.4702 868.55) 
(list 2560.4702 868.5603) 
(list 2560.4702 868.5706) 
(list 2560.4702 868.5808) 
(list 2560.4702 868.5911) 
(list 2560.4702 868.6014) 
(list 2560.4702 868.6117) 
(list 2560.4702 868.6219) 
(list 2560.4702 868.6322) 
(list 2560.4702 868.6425) 
(list 2560.4702 868.6528) 
(list 2560.4702 868.6631) 
(list 2560.4702 868.6733) 
(list 2560.4702 868.6836) 
(list 2560.4702 868.6939) 
(list 2560.4702 868.7042) 
(list 2560.4702 868.7144) 
(list 2560.4702 868.7247) 
(list 2560.4702 868.735) 
(list 2560.4702 868.7453) 
(list 2560.4702 868.7556) 
(list 2560.4702 868.7658) 
(list 2560.4702 868.7761) 
(list 2560.4702 868.7864) 
(list 2560.4702 868.7967) 
(list 2560.4702 868.8069) 
(list 2560.4702 868.8172) 
(list 2560.4702 868.8275) 
(list 2560.4702 868.8378) 
(list 2560.4702 868.8481) 
(list 2560.4702 868.8583) 
(list 2560.4702 868.8686) 
(list 2560.4702 868.8789) 
(list 2560.4702 868.8892) 
(list 2560.4702 868.8994) 
(list 2560.4702 868.9097) 
(list 2560.4702 868.92) 
(list 2561.106 868.92)))
(apply 'command (append '("pline") coords '("c")))
(setq tap8 (ssadd (entlast) tap8))
(command "_mirror" (entlast) "" "2560,900" "2560,901" "No")
(setq tap8 (ssadd (entlast) tap8))
(setq coords (list 
(list 2560 868.92) 
(list 2560.135 868.92) 
(list 2560.135 868.9303) 
(list 2560.135 868.9406) 
(list 2560.135 868.9508) 
(list 2560.135 868.9611) 
(list 2560.135 868.9714) 
(list 2560.135 868.9817) 
(list 2560.135 868.9919) 
(list 2560.135 869.0022) 
(list 2560.135 869.0125) 
(list 2560.135 869.0228) 
(list 2560.135 869.0331) 
(list 2560.135 869.0433) 
(list 2560.135 869.0536) 
(list 2560.135 869.0639) 
(list 2560.135 869.0742) 
(list 2560.135 869.0844) 
(list 2560.135 869.0947) 
(list 2560.135 869.105) 
(list 2560.135 869.1153) 
(list 2560.135 869.1256) 
(list 2560.135 869.1358) 
(list 2560.135 869.1461) 
(list 2560.135 869.1564) 
(list 2560.135 869.1667) 
(list 2560.135 869.1769) 
(list 2560.135 869.1872) 
(list 2560.135 869.1975) 
(list 2560.135 869.2078) 
(list 2560.135 869.2181) 
(list 2560.135 869.2283) 
(list 2560.135 869.2386) 
(list 2560.135 869.2489) 
(list 2560.135 869.2592) 
(list 2560.135 869.2694) 
(list 2560.135 869.2797) 
(list 2560.135 869.29) 
(list 2560 869.29)))
(apply 'command (append '("pline") coords '("c")))
(setq tap8 (ssadd (entlast) tap8))
(command "_mirror" (entlast) "" "2560,900" "2560,901" "No")
(setq tap8 (ssadd (entlast) tap8))
(setq coords (list 
(list 2560.4794 868.92) 
(list 2560.4702 868.92) 
(list 2560.4696 868.9303) 
(list 2560.4674 868.9406) 
(list 2560.4635 868.9508) 
(list 2560.4582 868.9611) 
(list 2560.4514 868.9714) 
(list 2560.4436 868.9817) 
(list 2560.4348 868.9919) 
(list 2560.4253 869.0022) 
(list 2560.4154 869.0125) 
(list 2560.4055 869.0228) 
(list 2560.3957 869.0331) 
(list 2560.3865 869.0433) 
(list 2560.3781 869.0536) 
(list 2560.3707 869.0639) 
(list 2560.3647 869.0742) 
(list 2560.3601 869.0844) 
(list 2560.3572 869.0947) 
(list 2560.3561 869.105) 
(list 2560.3567 869.1153) 
(list 2560.3592 869.1256) 
(list 2560.3634 869.1358) 
(list 2560.3692 869.1461) 
(list 2560.3765 869.1564) 
(list 2560.385 869.1667) 
(list 2560.3945 869.1769) 
(list 2560.4048 869.1872) 
(list 2560.4154 869.1975) 
(list 2560.4262 869.2078) 
(list 2560.4367 869.2181) 
(list 2560.4467 869.2283) 
(list 2560.4557 869.2386) 
(list 2560.4637 869.2489) 
(list 2560.4702 869.2592) 
(list 2560.4751 869.2694) 
(list 2560.4782 869.2797) 
(list 2560.4794 869.29) 
(list 2560.4794 869.29)))
(apply 'command (append '("pline") coords '("c")))
(setq tap8 (ssadd (entlast) tap8))
(command "_mirror" (entlast) "" "2560,900" "2560,901" "No")
(setq tap8 (ssadd (entlast) tap8))
(setq coords (list 
(list 2561.106 868.92) 
(list 2560.4794 868.92) 
(list 2560.4794 868.9303) 
(list 2560.4794 868.9406) 
(list 2560.4794 868.9508) 
(list 2560.4794 868.9611) 
(list 2560.4794 868.9714) 
(list 2560.4794 868.9817) 
(list 2560.4794 868.9919) 
(list 2560.4794 869.0022) 
(list 2560.4794 869.0125) 
(list 2560.4794 869.0228) 
(list 2560.4794 869.0331) 
(list 2560.4794 869.0433) 
(list 2560.4794 869.0536) 
(list 2560.4794 869.0639) 
(list 2560.4794 869.0742) 
(list 2560.4794 869.0844) 
(list 2560.4794 869.0947) 
(list 2560.4794 869.105) 
(list 2560.4794 869.1153) 
(list 2560.4794 869.1256) 
(list 2560.4794 869.1358) 
(list 2560.4794 869.1461) 
(list 2560.4794 869.1564) 
(list 2560.4794 869.1667) 
(list 2560.4794 869.1769) 
(list 2560.4794 869.1872) 
(list 2560.4794 869.1975) 
(list 2560.4794 869.2078) 
(list 2560.4794 869.2181) 
(list 2560.4794 869.2283) 
(list 2560.4794 869.2386) 
(list 2560.4794 869.2489) 
(list 2560.4794 869.2592) 
(list 2560.4794 869.2694) 
(list 2560.4794 869.2797) 
(list 2560.4794 869.29) 
(list 2561.106 869.29)))
(apply 'command (append '("pline") coords '("c")))
(setq tap8 (ssadd (entlast) tap8))
(command "_mirror" (entlast) "" "2560,900" "2560,901" "No")
(setq tap8 (ssadd (entlast) tap8))
(setq coords (list 
(list 2560 869.29) 
(list 2560.135 869.29) 
(list 2560.135 869.3003) 
(list 2560.135 869.3106) 
(list 2560.135 869.3208) 
(list 2560.135 869.3311) 
(list 2560.135 869.3414) 
(list 2560.135 869.3517) 
(list 2560.135 869.3619) 
(list 2560.135 869.3722) 
(list 2560.135 869.3825) 
(list 2560.135 869.3928) 
(list 2560.135 869.4031) 
(list 2560.135 869.4133) 
(list 2560.135 869.4236) 
(list 2560.135 869.4339) 
(list 2560.135 869.4442) 
(list 2560.135 869.4544) 
(list 2560.135 869.4647) 
(list 2560.135 869.475) 
(list 2560.135 869.4853) 
(list 2560.135 869.4956) 
(list 2560.135 869.5058) 
(list 2560.135 869.5161) 
(list 2560.135 869.5264) 
(list 2560.135 869.5367) 
(list 2560.135 869.5469) 
(list 2560.135 869.5572) 
(list 2560.135 869.5675) 
(list 2560.135 869.5778) 
(list 2560.135 869.5881) 
(list 2560.135 869.5983) 
(list 2560.135 869.6086) 
(list 2560.135 869.6189) 
(list 2560.135 869.6292) 
(list 2560.135 869.6394) 
(list 2560.135 869.6497) 
(list 2560.135 869.66) 
(list 2560 869.66)))
(apply 'command (append '("pline") coords '("c")))
(setq tap8 (ssadd (entlast) tap8))
(command "_mirror" (entlast) "" "2560,900" "2560,901" "No")
(setq tap8 (ssadd (entlast) tap8))
(setq coords (list 
(list 2560.4886 869.29) 
(list 2560.4794 869.29) 
(list 2560.4787 869.3003) 
(list 2560.476 869.3106) 
(list 2560.4715 869.3208) 
(list 2560.4652 869.3311) 
(list 2560.4574 869.3414) 
(list 2560.4482 869.3517) 
(list 2560.438 869.3619) 
(list 2560.4269 869.3722) 
(list 2560.4155 869.3825) 
(list 2560.4039 869.3928) 
(list 2560.3927 869.4031) 
(list 2560.382 869.4133) 
(list 2560.3723 869.4236) 
(list 2560.3638 869.4339) 
(list 2560.3568 869.4442) 
(list 2560.3516 869.4544) 
(list 2560.3483 869.4647) 
(list 2560.347 869.475) 
(list 2560.3478 869.4853) 
(list 2560.3507 869.4956) 
(list 2560.3555 869.5058) 
(list 2560.3623 869.5161) 
(list 2560.3707 869.5264) 
(list 2560.3805 869.5367) 
(list 2560.3915 869.5469) 
(list 2560.4033 869.5572) 
(list 2560.4155 869.5675) 
(list 2560.4279 869.5778) 
(list 2560.4399 869.5881) 
(list 2560.4513 869.5983) 
(list 2560.4617 869.6086) 
(list 2560.4707 869.6189) 
(list 2560.4781 869.6292) 
(list 2560.4837 869.6394) 
(list 2560.4872 869.6497) 
(list 2560.4886 869.66) 
(list 2560.4886 869.66)))
(apply 'command (append '("pline") coords '("c")))
(setq tap8 (ssadd (entlast) tap8))
(command "_mirror" (entlast) "" "2560,900" "2560,901" "No")
(setq tap8 (ssadd (entlast) tap8))
(setq coords (list 
(list 2561.106 869.29) 
(list 2560.4886 869.29) 
(list 2560.4886 869.3003) 
(list 2560.4886 869.3106) 
(list 2560.4886 869.3208) 
(list 2560.4886 869.3311) 
(list 2560.4886 869.3414) 
(list 2560.4886 869.3517) 
(list 2560.4886 869.3619) 
(list 2560.4886 869.3722) 
(list 2560.4886 869.3825) 
(list 2560.4886 869.3928) 
(list 2560.4886 869.4031) 
(list 2560.4886 869.4133) 
(list 2560.4886 869.4236) 
(list 2560.4886 869.4339) 
(list 2560.4886 869.4442) 
(list 2560.4886 869.4544) 
(list 2560.4886 869.4647) 
(list 2560.4886 869.475) 
(list 2560.4886 869.4853) 
(list 2560.4886 869.4956) 
(list 2560.4886 869.5058) 
(list 2560.4886 869.5161) 
(list 2560.4886 869.5264) 
(list 2560.4886 869.5367) 
(list 2560.4886 869.5469) 
(list 2560.4886 869.5572) 
(list 2560.4886 869.5675) 
(list 2560.4886 869.5778) 
(list 2560.4886 869.5881) 
(list 2560.4886 869.5983) 
(list 2560.4886 869.6086) 
(list 2560.4886 869.6189) 
(list 2560.4886 869.6292) 
(list 2560.4886 869.6394) 
(list 2560.4886 869.6497) 
(list 2560.4886 869.66) 
(list 2561.106 869.66)))
(apply 'command (append '("pline") coords '("c")))
(setq tap8 (ssadd (entlast) tap8))
(command "_mirror" (entlast) "" "2560,900" "2560,901" "No")
(setq tap8 (ssadd (entlast) tap8))
(setq coords (list 
(list 2560 869.66) 
(list 2560.135 869.66) 
(list 2560.135 869.6703) 
(list 2560.135 869.6806) 
(list 2560.135 869.6908) 
(list 2560.135 869.7011) 
(list 2560.135 869.7114) 
(list 2560.135 869.7217) 
(list 2560.135 869.7319) 
(list 2560.135 869.7422) 
(list 2560.135 869.7525) 
(list 2560.135 869.7628) 
(list 2560.135 869.7731) 
(list 2560.135 869.7833) 
(list 2560.135 869.7936) 
(list 2560.135 869.8039) 
(list 2560.135 869.8142) 
(list 2560.135 869.8244) 
(list 2560.135 869.8347) 
(list 2560.135 869.845) 
(list 2560.135 869.8553) 
(list 2560.135 869.8656) 
(list 2560.135 869.8758) 
(list 2560.135 869.8861) 
(list 2560.135 869.8964) 
(list 2560.135 869.9067) 
(list 2560.135 869.9169) 
(list 2560.135 869.9272) 
(list 2560.135 869.9375) 
(list 2560.135 869.9478) 
(list 2560.135 869.9581) 
(list 2560.135 869.9683) 
(list 2560.135 869.9786) 
(list 2560.135 869.9889) 
(list 2560.135 869.9992) 
(list 2560.135 870.0094) 
(list 2560.135 870.0197) 
(list 2560.135 870.03) 
(list 2560 870.03)))
(apply 'command (append '("pline") coords '("c")))
(setq tap8 (ssadd (entlast) tap8))
(command "_mirror" (entlast) "" "2560,900" "2560,901" "No")
(setq tap8 (ssadd (entlast) tap8))
(setq coords (list 
(list 2560.4978 869.66) 
(list 2560.4886 869.66) 
(list 2560.4877 869.6703) 
(list 2560.4847 869.6806) 
(list 2560.4795 869.6908) 
(list 2560.4723 869.7011) 
(list 2560.4633 869.7114) 
(list 2560.4528 869.7217) 
(list 2560.4411 869.7319) 
(list 2560.4286 869.7422) 
(list 2560.4156 869.7525) 
(list 2560.4024 869.7628) 
(list 2560.3896 869.7731) 
(list 2560.3775 869.7833) 
(list 2560.3665 869.7936) 
(list 2560.3569 869.8039) 
(list 2560.349 869.8142) 
(list 2560.3431 869.8244) 
(list 2560.3394 869.8347) 
(list 2560.3379 869.845) 
(list 2560.3389 869.8553) 
(list 2560.3421 869.8656) 
(list 2560.3477 869.8758) 
(list 2560.3553 869.8861) 
(list 2560.3649 869.8964) 
(list 2560.376 869.9067) 
(list 2560.3884 869.9169) 
(list 2560.4017 869.9272) 
(list 2560.4156 869.9375) 
(list 2560.4295 869.9478) 
(list 2560.4431 869.9581) 
(list 2560.4559 869.9683) 
(list 2560.4676 869.9786) 
(list 2560.4778 869.9889) 
(list 2560.4861 869.9992) 
(list 2560.4924 870.0094) 
(list 2560.4963 870.0197) 
(list 2560.4978 870.03) 
(list 2560.4978 870.03)))
(apply 'command (append '("pline") coords '("c")))
(setq tap8 (ssadd (entlast) tap8))
(command "_mirror" (entlast) "" "2560,900" "2560,901" "No")
(setq tap8 (ssadd (entlast) tap8))
(setq coords (list 
(list 2561.106 869.66) 
(list 2560.4978 869.66) 
(list 2560.4978 869.6703) 
(list 2560.4978 869.6806) 
(list 2560.4978 869.6908) 
(list 2560.4978 869.7011) 
(list 2560.4978 869.7114) 
(list 2560.4978 869.7217) 
(list 2560.4978 869.7319) 
(list 2560.4978 869.7422) 
(list 2560.4978 869.7525) 
(list 2560.4978 869.7628) 
(list 2560.4978 869.7731) 
(list 2560.4978 869.7833) 
(list 2560.4978 869.7936) 
(list 2560.4978 869.8039) 
(list 2560.4978 869.8142) 
(list 2560.4978 869.8244) 
(list 2560.4978 869.8347) 
(list 2560.4978 869.845) 
(list 2560.4978 869.8553) 
(list 2560.4978 869.8656) 
(list 2560.4978 869.8758) 
(list 2560.4978 869.8861) 
(list 2560.4978 869.8964) 
(list 2560.4978 869.9067) 
(list 2560.4978 869.9169) 
(list 2560.4978 869.9272) 
(list 2560.4978 869.9375) 
(list 2560.4978 869.9478) 
(list 2560.4978 869.9581) 
(list 2560.4978 869.9683) 
(list 2560.4978 869.9786) 
(list 2560.4978 869.9889) 
(list 2560.4978 869.9992) 
(list 2560.4978 870.0094) 
(list 2560.4978 870.0197) 
(list 2560.4978 870.03) 
(list 2561.106 870.03)))
(apply 'command (append '("pline") coords '("c")))
(setq tap8 (ssadd (entlast) tap8))
(command "_mirror" (entlast) "" "2560,900" "2560,901" "No")
(setq tap8 (ssadd (entlast) tap8))
(setq coords (list 
(list 2560 870.03) 
(list 2560.135 870.03) 
(list 2560.135 870.0403) 
(list 2560.135 870.0506) 
(list 2560.135 870.0608) 
(list 2560.135 870.0711) 
(list 2560.135 870.0814) 
(list 2560.135 870.0917) 
(list 2560.135 870.1019) 
(list 2560.135 870.1122) 
(list 2560.135 870.1225) 
(list 2560.135 870.1328) 
(list 2560.135 870.1431) 
(list 2560.135 870.1533) 
(list 2560.135 870.1636) 
(list 2560.135 870.1739) 
(list 2560.135 870.1842) 
(list 2560.135 870.1944) 
(list 2560.135 870.2047) 
(list 2560.135 870.215) 
(list 2560.135 870.2253) 
(list 2560.135 870.2356) 
(list 2560.135 870.2458) 
(list 2560.135 870.2561) 
(list 2560.135 870.2664) 
(list 2560.135 870.2767) 
(list 2560.135 870.2869) 
(list 2560.135 870.2972) 
(list 2560.135 870.3075) 
(list 2560.135 870.3178) 
(list 2560.135 870.3281) 
(list 2560.135 870.3383) 
(list 2560.135 870.3486) 
(list 2560.135 870.3589) 
(list 2560.135 870.3692) 
(list 2560.135 870.3794) 
(list 2560.135 870.3897) 
(list 2560.135 870.4) 
(list 2560 870.4)))
(apply 'command (append '("pline") coords '("c")))
(setq tap8 (ssadd (entlast) tap8))
(command "_mirror" (entlast) "" "2560,900" "2560,901" "No")
(setq tap8 (ssadd (entlast) tap8))
(setq coords (list 
(list 2560.507 870.03) 
(list 2560.4978 870.03) 
(list 2560.4968 870.0403) 
(list 2560.4933 870.0506) 
(list 2560.4875 870.0608) 
(list 2560.4794 870.0711) 
(list 2560.4693 870.0814) 
(list 2560.4575 870.0917) 
(list 2560.4443 870.1019) 
(list 2560.4302 870.1122) 
(list 2560.4156 870.1225) 
(list 2560.4009 870.1328) 
(list 2560.3866 870.1431) 
(list 2560.373 870.1533) 
(list 2560.3607 870.1636) 
(list 2560.3499 870.1739) 
(list 2560.3411 870.1842) 
(list 2560.3346 870.1944) 
(list 2560.3304 870.2047) 
(list 2560.3289 870.215) 
(list 2560.3299 870.2253) 
(list 2560.3336 870.2356) 
(list 2560.3398 870.2458) 
(list 2560.3484 870.2561) 
(list 2560.3591 870.2664) 
(list 2560.3715 870.2767) 
(list 2560.3854 870.2869) 
(list 2560.4002 870.2972) 
(list 2560.4156 870.3075) 
(list 2560.4312 870.3178) 
(list 2560.4463 870.3281) 
(list 2560.4606 870.3383) 
(list 2560.4736 870.3486) 
(list 2560.4848 870.3589) 
(list 2560.4941 870.3692) 
(list 2560.501 870.3794) 
(list 2560.5054 870.3897) 
(list 2560.507 870.4) 
(list 2560.507 870.4)))
(apply 'command (append '("pline") coords '("c")))
(setq tap8 (ssadd (entlast) tap8))
(command "_mirror" (entlast) "" "2560,900" "2560,901" "No")
(setq tap8 (ssadd (entlast) tap8))
(setq coords (list 
(list 2561.106 870.03) 
(list 2560.507 870.03) 
(list 2560.507 870.0403) 
(list 2560.507 870.0506) 
(list 2560.507 870.0608) 
(list 2560.507 870.0711) 
(list 2560.507 870.0814) 
(list 2560.507 870.0917) 
(list 2560.507 870.1019) 
(list 2560.507 870.1122) 
(list 2560.507 870.1225) 
(list 2560.507 870.1328) 
(list 2560.507 870.1431) 
(list 2560.507 870.1533) 
(list 2560.507 870.1636) 
(list 2560.507 870.1739) 
(list 2560.507 870.1842) 
(list 2560.507 870.1944) 
(list 2560.507 870.2047) 
(list 2560.507 870.215) 
(list 2560.507 870.2253) 
(list 2560.507 870.2356) 
(list 2560.507 870.2458) 
(list 2560.507 870.2561) 
(list 2560.507 870.2664) 
(list 2560.507 870.2767) 
(list 2560.507 870.2869) 
(list 2560.507 870.2972) 
(list 2560.507 870.3075) 
(list 2560.507 870.3178) 
(list 2560.507 870.3281) 
(list 2560.507 870.3383) 
(list 2560.507 870.3486) 
(list 2560.507 870.3589) 
(list 2560.507 870.3692) 
(list 2560.507 870.3794) 
(list 2560.507 870.3897) 
(list 2560.507 870.4) 
(list 2561.106 870.4)))
(apply 'command (append '("pline") coords '("c")))
(setq tap8 (ssadd (entlast) tap8))
(command "_mirror" (entlast) "" "2560,900" "2560,901" "No")
(setq tap8 (ssadd (entlast) tap8))
(setq coords (list 
(list 2560 870.4) 
(list 2560.135 870.4) 
(list 2560.135 870.4103) 
(list 2560.135 870.4206) 
(list 2560.135 870.4308) 
(list 2560.135 870.4411) 
(list 2560.135 870.4514) 
(list 2560.135 870.4617) 
(list 2560.135 870.4719) 
(list 2560.135 870.4822) 
(list 2560.135 870.4925) 
(list 2560.135 870.5028) 
(list 2560.135 870.5131) 
(list 2560.135 870.5233) 
(list 2560.135 870.5336) 
(list 2560.135 870.5439) 
(list 2560.135 870.5542) 
(list 2560.135 870.5644) 
(list 2560.135 870.5747) 
(list 2560.135 870.585) 
(list 2560.135 870.5953) 
(list 2560.135 870.6056) 
(list 2560.135 870.6158) 
(list 2560.135 870.6261) 
(list 2560.135 870.6364) 
(list 2560.135 870.6467) 
(list 2560.135 870.6569) 
(list 2560.135 870.6672) 
(list 2560.135 870.6775) 
(list 2560.135 870.6878) 
(list 2560.135 870.6981) 
(list 2560.135 870.7083) 
(list 2560.135 870.7186) 
(list 2560.135 870.7289) 
(list 2560.135 870.7392) 
(list 2560.135 870.7494) 
(list 2560.135 870.7597) 
(list 2560.135 870.77) 
(list 2560 870.77)))
(apply 'command (append '("pline") coords '("c")))
(setq tap8 (ssadd (entlast) tap8))
(command "_mirror" (entlast) "" "2560,900" "2560,901" "No")
(setq tap8 (ssadd (entlast) tap8))
(setq coords (list 
(list 2560.5162 870.4) 
(list 2560.507 870.4) 
(list 2560.5059 870.4103) 
(list 2560.502 870.4206) 
(list 2560.4954 870.4308) 
(list 2560.4864 870.4411) 
(list 2560.4752 870.4514) 
(list 2560.4621 870.4617) 
(list 2560.4475 870.4719) 
(list 2560.4319 870.4822) 
(list 2560.4157 870.4925) 
(list 2560.3994 870.5028) 
(list 2560.3835 870.5131) 
(list 2560.3685 870.5233) 
(list 2560.3549 870.5336) 
(list 2560.343 870.5439) 
(list 2560.3333 870.5542) 
(list 2560.3261 870.5644) 
(list 2560.3215 870.5747) 
(list 2560.3198 870.585) 
(list 2560.321 870.5953) 
(list 2560.3251 870.6056) 
(list 2560.332 870.6158) 
(list 2560.3415 870.6261) 
(list 2560.3533 870.6364) 
(list 2560.367 870.6467) 
(list 2560.3823 870.6569) 
(list 2560.3987 870.6672) 
(list 2560.4157 870.6775) 
(list 2560.4328 870.6878) 
(list 2560.4495 870.6981) 
(list 2560.4652 870.7083) 
(list 2560.4795 870.7186) 
(list 2560.4919 870.7289) 
(list 2560.5021 870.7392) 
(list 2560.5097 870.7494) 
(list 2560.5144 870.7597) 
(list 2560.5162 870.77) 
(list 2560.5162 870.77)))
(apply 'command (append '("pline") coords '("c")))
(setq tap8 (ssadd (entlast) tap8))
(command "_mirror" (entlast) "" "2560,900" "2560,901" "No")
(setq tap8 (ssadd (entlast) tap8))
(setq coords (list 
(list 2561.106 870.4) 
(list 2560.5162 870.4) 
(list 2560.5162 870.4103) 
(list 2560.5162 870.4206) 
(list 2560.5162 870.4308) 
(list 2560.5162 870.4411) 
(list 2560.5162 870.4514) 
(list 2560.5162 870.4617) 
(list 2560.5162 870.4719) 
(list 2560.5162 870.4822) 
(list 2560.5162 870.4925) 
(list 2560.5162 870.5028) 
(list 2560.5162 870.5131) 
(list 2560.5162 870.5233) 
(list 2560.5162 870.5336) 
(list 2560.5162 870.5439) 
(list 2560.5162 870.5542) 
(list 2560.5162 870.5644) 
(list 2560.5162 870.5747) 
(list 2560.5162 870.585) 
(list 2560.5162 870.5953) 
(list 2560.5162 870.6056) 
(list 2560.5162 870.6158) 
(list 2560.5162 870.6261) 
(list 2560.5162 870.6364) 
(list 2560.5162 870.6467) 
(list 2560.5162 870.6569) 
(list 2560.5162 870.6672) 
(list 2560.5162 870.6775) 
(list 2560.5162 870.6878) 
(list 2560.5162 870.6981) 
(list 2560.5162 870.7083) 
(list 2560.5162 870.7186) 
(list 2560.5162 870.7289) 
(list 2560.5162 870.7392) 
(list 2560.5162 870.7494) 
(list 2560.5162 870.7597) 
(list 2560.5162 870.77) 
(list 2561.106 870.77)))
(apply 'command (append '("pline") coords '("c")))
(setq tap8 (ssadd (entlast) tap8))
(command "_mirror" (entlast) "" "2560,900" "2560,901" "No")
(setq tap8 (ssadd (entlast) tap8))
(setq coords (list 
(list 2560 870.77) 
(list 2560.135 870.77) 
(list 2560.135 870.7803) 
(list 2560.135 870.7906) 
(list 2560.135 870.8008) 
(list 2560.135 870.8111) 
(list 2560.135 870.8214) 
(list 2560.135 870.8317) 
(list 2560.135 870.8419) 
(list 2560.135 870.8522) 
(list 2560.135 870.8625) 
(list 2560.135 870.8728) 
(list 2560.135 870.8831) 
(list 2560.135 870.8933) 
(list 2560.135 870.9036) 
(list 2560.135 870.9139) 
(list 2560.135 870.9242) 
(list 2560.135 870.9344) 
(list 2560.135 870.9447) 
(list 2560.135 870.955) 
(list 2560.135 870.9653) 
(list 2560.135 870.9756) 
(list 2560.135 870.9858) 
(list 2560.135 870.9961) 
(list 2560.135 871.0064) 
(list 2560.135 871.0167) 
(list 2560.135 871.0269) 
(list 2560.135 871.0372) 
(list 2560.135 871.0475) 
(list 2560.135 871.0578) 
(list 2560.135 871.0681) 
(list 2560.135 871.0783) 
(list 2560.135 871.0886) 
(list 2560.135 871.0989) 
(list 2560.135 871.1092) 
(list 2560.135 871.1194) 
(list 2560.135 871.1297) 
(list 2560.135 871.14) 
(list 2560 871.14)))
(apply 'command (append '("pline") coords '("c")))
(setq tap8 (ssadd (entlast) tap8))
(command "_mirror" (entlast) "" "2560,900" "2560,901" "No")
(setq tap8 (ssadd (entlast) tap8))
(setq coords (list 
(list 2560.5254 870.77) 
(list 2560.5162 870.77) 
(list 2560.5149 870.7803) 
(list 2560.5106 870.7906) 
(list 2560.5034 870.8008) 
(list 2560.4935 870.8111) 
(list 2560.4811 870.8214) 
(list 2560.4667 870.8317) 
(list 2560.4507 870.8419) 
(list 2560.4335 870.8522) 
(list 2560.4158 870.8625) 
(list 2560.3979 870.8728) 
(list 2560.3804 870.8831) 
(list 2560.364 870.8933) 
(list 2560.3491 870.9036) 
(list 2560.3361 870.9139) 
(list 2560.3255 870.9242) 
(list 2560.3175 870.9344) 
(list 2560.3126 870.9447) 
(list 2560.3107 870.955) 
(list 2560.3121 870.9653) 
(list 2560.3166 870.9756) 
(list 2560.3242 870.9858) 
(list 2560.3345 870.9961) 
(list 2560.3474 871.0064) 
(list 2560.3625 871.0167) 
(list 2560.3792 871.0269) 
(list 2560.3972 871.0372) 
(list 2560.4158 871.0475) 
(list 2560.4345 871.0578) 
(list 2560.4527 871.0681) 
(list 2560.4698 871.0783) 
(list 2560.4854 871.0886) 
(list 2560.499 871.0989) 
(list 2560.5101 871.1092) 
(list 2560.5183 871.1194) 
(list 2560.5235 871.1297) 
(list 2560.5254 871.14) 
(list 2560.5254 871.14)))
(apply 'command (append '("pline") coords '("c")))
(setq tap8 (ssadd (entlast) tap8))
(command "_mirror" (entlast) "" "2560,900" "2560,901" "No")
(setq tap8 (ssadd (entlast) tap8))
(setq coords (list 
(list 2561.106 870.77) 
(list 2560.5254 870.77) 
(list 2560.5254 870.7803) 
(list 2560.5254 870.7906) 
(list 2560.5254 870.8008) 
(list 2560.5254 870.8111) 
(list 2560.5254 870.8214) 
(list 2560.5254 870.8317) 
(list 2560.5254 870.8419) 
(list 2560.5254 870.8522) 
(list 2560.5254 870.8625) 
(list 2560.5254 870.8728) 
(list 2560.5254 870.8831) 
(list 2560.5254 870.8933) 
(list 2560.5254 870.9036) 
(list 2560.5254 870.9139) 
(list 2560.5254 870.9242) 
(list 2560.5254 870.9344) 
(list 2560.5254 870.9447) 
(list 2560.5254 870.955) 
(list 2560.5254 870.9653) 
(list 2560.5254 870.9756) 
(list 2560.5254 870.9858) 
(list 2560.5254 870.9961) 
(list 2560.5254 871.0064) 
(list 2560.5254 871.0167) 
(list 2560.5254 871.0269) 
(list 2560.5254 871.0372) 
(list 2560.5254 871.0475) 
(list 2560.5254 871.0578) 
(list 2560.5254 871.0681) 
(list 2560.5254 871.0783) 
(list 2560.5254 871.0886) 
(list 2560.5254 871.0989) 
(list 2560.5254 871.1092) 
(list 2560.5254 871.1194) 
(list 2560.5254 871.1297) 
(list 2560.5254 871.14) 
(list 2561.106 871.14)))
(apply 'command (append '("pline") coords '("c")))
(setq tap8 (ssadd (entlast) tap8))
(command "_mirror" (entlast) "" "2560,900" "2560,901" "No")
(setq tap8 (ssadd (entlast) tap8))
(setq coords (list 
(list 2560 871.14) 
(list 2560.135 871.14) 
(list 2560.135 871.1503) 
(list 2560.135 871.1606) 
(list 2560.135 871.1708) 
(list 2560.135 871.1811) 
(list 2560.135 871.1914) 
(list 2560.135 871.2017) 
(list 2560.135 871.2119) 
(list 2560.135 871.2222) 
(list 2560.135 871.2325) 
(list 2560.135 871.2428) 
(list 2560.135 871.2531) 
(list 2560.135 871.2633) 
(list 2560.135 871.2736) 
(list 2560.135 871.2839) 
(list 2560.135 871.2942) 
(list 2560.135 871.3044) 
(list 2560.135 871.3147) 
(list 2560.135 871.325) 
(list 2560.135 871.3353) 
(list 2560.135 871.3456) 
(list 2560.135 871.3558) 
(list 2560.135 871.3661) 
(list 2560.135 871.3764) 
(list 2560.135 871.3867) 
(list 2560.135 871.3969) 
(list 2560.135 871.4072) 
(list 2560.135 871.4175) 
(list 2560.135 871.4278) 
(list 2560.135 871.4381) 
(list 2560.135 871.4483) 
(list 2560.135 871.4586) 
(list 2560.135 871.4689) 
(list 2560.135 871.4792) 
(list 2560.135 871.4894) 
(list 2560.135 871.4997) 
(list 2560.135 871.51) 
(list 2560 871.51)))
(apply 'command (append '("pline") coords '("c")))
(setq tap8 (ssadd (entlast) tap8))
(command "_mirror" (entlast) "" "2560,900" "2560,901" "No")
(setq tap8 (ssadd (entlast) tap8))
(setq coords (list 
(list 2560.5346 871.14) 
(list 2560.5254 871.14) 
(list 2560.524 871.1503) 
(list 2560.5193 871.1606) 
(list 2560.5114 871.1708) 
(list 2560.5005 871.1811) 
(list 2560.4871 871.1914) 
(list 2560.4714 871.2017) 
(list 2560.4539 871.2119) 
(list 2560.4352 871.2222) 
(list 2560.4158 871.2325) 
(list 2560.3963 871.2428) 
(list 2560.3774 871.2531) 
(list 2560.3595 871.2633) 
(list 2560.3433 871.2736) 
(list 2560.3291 871.2839) 
(list 2560.3176 871.2942) 
(list 2560.309 871.3044) 
(list 2560.3036 871.3147) 
(list 2560.3017 871.325) 
(list 2560.3032 871.3353) 
(list 2560.3081 871.3456) 
(list 2560.3163 871.3558) 
(list 2560.3276 871.3661) 
(list 2560.3416 871.3764) 
(list 2560.358 871.3867) 
(list 2560.3762 871.3969) 
(list 2560.3957 871.4072) 
(list 2560.4158 871.4175) 
(list 2560.4361 871.4278) 
(list 2560.4559 871.4381) 
(list 2560.4745 871.4483) 
(list 2560.4914 871.4586) 
(list 2560.506 871.4689) 
(list 2560.518 871.4792) 
(list 2560.527 871.4894) 
(list 2560.5325 871.4997) 
(list 2560.5346 871.51) 
(list 2560.5346 871.51)))
(apply 'command (append '("pline") coords '("c")))
(setq tap8 (ssadd (entlast) tap8))
(command "_mirror" (entlast) "" "2560,900" "2560,901" "No")
(setq tap8 (ssadd (entlast) tap8))
(setq coords (list 
(list 2561.106 871.14) 
(list 2560.5346 871.14) 
(list 2560.5346 871.1503) 
(list 2560.5346 871.1606) 
(list 2560.5346 871.1708) 
(list 2560.5346 871.1811) 
(list 2560.5346 871.1914) 
(list 2560.5346 871.2017) 
(list 2560.5346 871.2119) 
(list 2560.5346 871.2222) 
(list 2560.5346 871.2325) 
(list 2560.5346 871.2428) 
(list 2560.5346 871.2531) 
(list 2560.5346 871.2633) 
(list 2560.5346 871.2736) 
(list 2560.5346 871.2839) 
(list 2560.5346 871.2942) 
(list 2560.5346 871.3044) 
(list 2560.5346 871.3147) 
(list 2560.5346 871.325) 
(list 2560.5346 871.3353) 
(list 2560.5346 871.3456) 
(list 2560.5346 871.3558) 
(list 2560.5346 871.3661) 
(list 2560.5346 871.3764) 
(list 2560.5346 871.3867) 
(list 2560.5346 871.3969) 
(list 2560.5346 871.4072) 
(list 2560.5346 871.4175) 
(list 2560.5346 871.4278) 
(list 2560.5346 871.4381) 
(list 2560.5346 871.4483) 
(list 2560.5346 871.4586) 
(list 2560.5346 871.4689) 
(list 2560.5346 871.4792) 
(list 2560.5346 871.4894) 
(list 2560.5346 871.4997) 
(list 2560.5346 871.51) 
(list 2561.106 871.51)))
(apply 'command (append '("pline") coords '("c")))
(setq tap8 (ssadd (entlast) tap8))
(command "_mirror" (entlast) "" "2560,900" "2560,901" "No")
(setq tap8 (ssadd (entlast) tap8))
(setq coords (list 
(list 2560 871.51) 
(list 2560.135 871.51) 
(list 2560.135 871.5203) 
(list 2560.135 871.5306) 
(list 2560.135 871.5408) 
(list 2560.135 871.5511) 
(list 2560.135 871.5614) 
(list 2560.135 871.5717) 
(list 2560.135 871.5819) 
(list 2560.135 871.5922) 
(list 2560.135 871.6025) 
(list 2560.135 871.6128) 
(list 2560.135 871.6231) 
(list 2560.135 871.6333) 
(list 2560.135 871.6436) 
(list 2560.135 871.6539) 
(list 2560.135 871.6642) 
(list 2560.135 871.6744) 
(list 2560.135 871.6847) 
(list 2560.135 871.695) 
(list 2560.135 871.7053) 
(list 2560.135 871.7156) 
(list 2560.135 871.7258) 
(list 2560.135 871.7361) 
(list 2560.135 871.7464) 
(list 2560.135 871.7567) 
(list 2560.135 871.7669) 
(list 2560.135 871.7772) 
(list 2560.135 871.7875) 
(list 2560.135 871.7978) 
(list 2560.135 871.8081) 
(list 2560.135 871.8183) 
(list 2560.135 871.8286) 
(list 2560.135 871.8389) 
(list 2560.135 871.8492) 
(list 2560.135 871.8594) 
(list 2560.135 871.8697) 
(list 2560.135 871.88) 
(list 2560 871.88)))
(apply 'command (append '("pline") coords '("c")))
(setq tap8 (ssadd (entlast) tap8))
(command "_mirror" (entlast) "" "2560,900" "2560,901" "No")
(setq tap8 (ssadd (entlast) tap8))
(setq coords (list 
(list 2560.5438 871.51) 
(list 2560.5346 871.51) 
(list 2560.533 871.5203) 
(list 2560.5279 871.5306) 
(list 2560.5194 871.5408) 
(list 2560.5076 871.5511) 
(list 2560.493 871.5614) 
(list 2560.476 871.5717) 
(list 2560.4571 871.5819) 
(list 2560.4369 871.5922) 
(list 2560.4159 871.6025) 
(list 2560.3948 871.6128) 
(list 2560.3743 871.6231) 
(list 2560.355 871.6333) 
(list 2560.3375 871.6436) 
(list 2560.3222 871.6539) 
(list 2560.3098 871.6642) 
(list 2560.3005 871.6744) 
(list 2560.2947 871.6847) 
(list 2560.2926 871.695) 
(list 2560.2942 871.7053) 
(list 2560.2996 871.7156) 
(list 2560.3085 871.7258) 
(list 2560.3207 871.7361) 
(list 2560.3358 871.7464) 
(list 2560.3535 871.7567) 
(list 2560.3731 871.7669) 
(list 2560.3942 871.7772) 
(list 2560.4159 871.7875) 
(list 2560.4378 871.7978) 
(list 2560.459 871.8081) 
(list 2560.4791 871.8183) 
(list 2560.4973 871.8286) 
(list 2560.5131 871.8389) 
(list 2560.526 871.8492) 
(list 2560.5356 871.8594) 
(list 2560.5416 871.8697) 
(list 2560.5438 871.88) 
(list 2560.5438 871.88)))
(apply 'command (append '("pline") coords '("c")))
(setq tap8 (ssadd (entlast) tap8))
(command "_mirror" (entlast) "" "2560,900" "2560,901" "No")
(setq tap8 (ssadd (entlast) tap8))
(setq coords (list 
(list 2561.106 871.51) 
(list 2560.5438 871.51) 
(list 2560.5438 871.5203) 
(list 2560.5438 871.5306) 
(list 2560.5438 871.5408) 
(list 2560.5438 871.5511) 
(list 2560.5438 871.5614) 
(list 2560.5438 871.5717) 
(list 2560.5438 871.5819) 
(list 2560.5438 871.5922) 
(list 2560.5438 871.6025) 
(list 2560.5438 871.6128) 
(list 2560.5438 871.6231) 
(list 2560.5438 871.6333) 
(list 2560.5438 871.6436) 
(list 2560.5438 871.6539) 
(list 2560.5438 871.6642) 
(list 2560.5438 871.6744) 
(list 2560.5438 871.6847) 
(list 2560.5438 871.695) 
(list 2560.5438 871.7053) 
(list 2560.5438 871.7156) 
(list 2560.5438 871.7258) 
(list 2560.5438 871.7361) 
(list 2560.5438 871.7464) 
(list 2560.5438 871.7567) 
(list 2560.5438 871.7669) 
(list 2560.5438 871.7772) 
(list 2560.5438 871.7875) 
(list 2560.5438 871.7978) 
(list 2560.5438 871.8081) 
(list 2560.5438 871.8183) 
(list 2560.5438 871.8286) 
(list 2560.5438 871.8389) 
(list 2560.5438 871.8492) 
(list 2560.5438 871.8594) 
(list 2560.5438 871.8697) 
(list 2560.5438 871.88) 
(list 2561.106 871.88)))
(apply 'command (append '("pline") coords '("c")))
(setq tap8 (ssadd (entlast) tap8))
(command "_mirror" (entlast) "" "2560,900" "2560,901" "No")
(setq tap8 (ssadd (entlast) tap8))
(setq coords (list 
(list 2560 871.88) 
(list 2560.135 871.88) 
(list 2560.135 871.8903) 
(list 2560.135 871.9006) 
(list 2560.135 871.9108) 
(list 2560.135 871.9211) 
(list 2560.135 871.9314) 
(list 2560.135 871.9417) 
(list 2560.135 871.9519) 
(list 2560.135 871.9622) 
(list 2560.135 871.9725) 
(list 2560.135 871.9828) 
(list 2560.135 871.9931) 
(list 2560.135 872.0033) 
(list 2560.135 872.0136) 
(list 2560.135 872.0239) 
(list 2560.135 872.0342) 
(list 2560.135 872.0444) 
(list 2560.135 872.0547) 
(list 2560.135 872.065) 
(list 2560.135 872.0753) 
(list 2560.135 872.0856) 
(list 2560.135 872.0958) 
(list 2560.135 872.1061) 
(list 2560.135 872.1164) 
(list 2560.135 872.1267) 
(list 2560.135 872.1369) 
(list 2560.135 872.1472) 
(list 2560.135 872.1575) 
(list 2560.135 872.1678) 
(list 2560.135 872.1781) 
(list 2560.135 872.1883) 
(list 2560.135 872.1986) 
(list 2560.135 872.2089) 
(list 2560.135 872.2192) 
(list 2560.135 872.2294) 
(list 2560.135 872.2397) 
(list 2560.135 872.25) 
(list 2560 872.25)))
(apply 'command (append '("pline") coords '("c")))
(setq tap8 (ssadd (entlast) tap8))
(command "_mirror" (entlast) "" "2560,900" "2560,901" "No")
(setq tap8 (ssadd (entlast) tap8))
(setq coords (list 
(list 2560.553 871.88) 
(list 2560.5438 871.88) 
(list 2560.5421 871.8903) 
(list 2560.5366 871.9006) 
(list 2560.5273 871.9108) 
(list 2560.5147 871.9211) 
(list 2560.4989 871.9314) 
(list 2560.4806 871.9417) 
(list 2560.4603 871.9519) 
(list 2560.4385 871.9622) 
(list 2560.416 871.9725) 
(list 2560.3933 871.9828) 
(list 2560.3713 871.9931) 
(list 2560.3505 872.0033) 
(list 2560.3316 872.0136) 
(list 2560.3153 872.0239) 
(list 2560.3019 872.0342) 
(list 2560.292 872.0444) 
(list 2560.2858 872.0547) 
(list 2560.2835 872.065) 
(list 2560.2853 872.0753) 
(list 2560.291 872.0856) 
(list 2560.3006 872.0958) 
(list 2560.3137 872.1061) 
(list 2560.33 872.1164) 
(list 2560.349 872.1267) 
(list 2560.3701 872.1369) 
(list 2560.3926 872.1472) 
(list 2560.416 872.1575) 
(list 2560.4394 872.1678) 
(list 2560.4622 872.1781) 
(list 2560.4837 872.1883) 
(list 2560.5032 872.1986) 
(list 2560.5202 872.2089) 
(list 2560.534 872.2192) 
(list 2560.5443 872.2294) 
(list 2560.5507 872.2397) 
(list 2560.553 872.25) 
(list 2560.553 872.25)))
(apply 'command (append '("pline") coords '("c")))
(setq tap8 (ssadd (entlast) tap8))
(command "_mirror" (entlast) "" "2560,900" "2560,901" "No")
(setq tap8 (ssadd (entlast) tap8))
(setq coords (list 
(list 2561.106 871.88) 
(list 2560.553 871.88) 
(list 2560.553 871.8903) 
(list 2560.553 871.9006) 
(list 2560.553 871.9108) 
(list 2560.553 871.9211) 
(list 2560.553 871.9314) 
(list 2560.553 871.9417) 
(list 2560.553 871.9519) 
(list 2560.553 871.9622) 
(list 2560.553 871.9725) 
(list 2560.553 871.9828) 
(list 2560.553 871.9931) 
(list 2560.553 872.0033) 
(list 2560.553 872.0136) 
(list 2560.553 872.0239) 
(list 2560.553 872.0342) 
(list 2560.553 872.0444) 
(list 2560.553 872.0547) 
(list 2560.553 872.065) 
(list 2560.553 872.0753) 
(list 2560.553 872.0856) 
(list 2560.553 872.0958) 
(list 2560.553 872.1061) 
(list 2560.553 872.1164) 
(list 2560.553 872.1267) 
(list 2560.553 872.1369) 
(list 2560.553 872.1472) 
(list 2560.553 872.1575) 
(list 2560.553 872.1678) 
(list 2560.553 872.1781) 
(list 2560.553 872.1883) 
(list 2560.553 872.1986) 
(list 2560.553 872.2089) 
(list 2560.553 872.2192) 
(list 2560.553 872.2294) 
(list 2560.553 872.2397) 
(list 2560.553 872.25) 
(list 2561.106 872.25)))
(apply 'command (append '("pline") coords '("c")))
(setq tap8 (ssadd (entlast) tap8))
(command "_mirror" (entlast) "" "2560,900" "2560,901" "No")
(setq tap8 (ssadd (entlast) tap8))
(command "_block" "blktap8" "2560,900" tap8 "")
(command "_insert" "blktap8" "2560,900" "1" "1" "0")
(command "_insert" "blktap8" "2560,900" "1" "1" "180")
(setq uc8 nil)
(setq uc8 (ssadd))
(setq coords (list 
(list 0 -0.185) 
(list 0.135 -0.185) 
(list 0.135 -0.17472) 
(list 0.135 -0.16444) 
(list 0.135 -0.15417) 
(list 0.135 -0.14389) 
(list 0.135 -0.13361) 
(list 0.135 -0.12333) 
(list 0.135 -0.11306) 
(list 0.135 -0.10278) 
(list 0.135 -0.0925) 
(list 0.135 -0.082222) 
(list 0.135 -0.071944) 
(list 0.135 -0.061667) 
(list 0.135 -0.051389) 
(list 0.135 -0.041111) 
(list 0.135 -0.030833) 
(list 0.135 -0.020556) 
(list 0.135 -0.010278) 
(list 0.135 0) 
(list 0.135 0.010278) 
(list 0.135 0.020556) 
(list 0.135 0.030833) 
(list 0.135 0.041111) 
(list 0.135 0.051389) 
(list 0.135 0.061667) 
(list 0.135 0.071944) 
(list 0.135 0.082222) 
(list 0.135 0.0925) 
(list 0.135 0.10278) 
(list 0.135 0.11306) 
(list 0.135 0.12333) 
(list 0.135 0.13361) 
(list 0.135 0.14389) 
(list 0.135 0.15417) 
(list 0.135 0.16444) 
(list 0.135 0.17472) 
(list 0.135 0.185) 
(list 0 0.185)))
(apply 'command (append '("pline") coords '("c")))
(setq uc8 (ssadd (entlast) uc8))
(setq coords (list 
(list 1.106 -0.185) 
(list 0.553 -0.185) 
(list 0.55092 -0.17472) 
(list 0.54474 -0.16444) 
(list 0.53465 -0.15417) 
(list 0.52095 -0.14389) 
(list 0.50406 -0.13361) 
(list 0.4845 -0.12333) 
(list 0.46286 -0.11306) 
(list 0.43979 -0.10278) 
(list 0.416 -0.0925) 
(list 0.39221 -0.082222) 
(list 0.36914 -0.071944) 
(list 0.3475 -0.061667) 
(list 0.32794 -0.051389) 
(list 0.31105 -0.041111) 
(list 0.29735 -0.030833) 
(list 0.28726 -0.020556) 
(list 0.28108 -0.010278) 
(list 0.279 0) 
(list 0.28108 0.010278) 
(list 0.28726 0.020556) 
(list 0.29735 0.030833) 
(list 0.31105 0.041111) 
(list 0.32794 0.051389) 
(list 0.3475 0.061667) 
(list 0.36914 0.071944) 
(list 0.39221 0.082222) 
(list 0.416 0.0925) 
(list 0.43979 0.10278) 
(list 0.46286 0.11306) 
(list 0.4845 0.12333) 
(list 0.50406 0.13361) 
(list 0.52095 0.14389) 
(list 0.53465 0.15417) 
(list 0.54474 0.16444) 
(list 0.55092 0.17472) 
(list 0.553 0.185) 
(list 1.106 0.185)))
(apply 'command (append '("pline") coords '("c")))
(setq uc8 (ssadd (entlast) uc8))
(command "_block" "blkuc8" "0,0.185" uc8 "")
(command "_insert" "blkuc8" "2560,872.62" "1" "1" "0")
(command "_insert" "blkuc8" "2560,872.25" "1" "1" "180")
(command "_insert" "blkuc8" "2560,872.99" "1" "1" "0")
(command "_insert" "blkuc8" "2560,872.62" "1" "1" "180")
(command "_insert" "blkuc8" "2560,873.36" "1" "1" "0")
(command "_insert" "blkuc8" "2560,872.99" "1" "1" "180")
(command "_insert" "blkuc8" "2560,873.73" "1" "1" "0")
(command "_insert" "blkuc8" "2560,873.36" "1" "1" "180")
(command "_insert" "blkuc8" "2560,874.1" "1" "1" "0")
(command "_insert" "blkuc8" "2560,873.73" "1" "1" "180")
(command "_insert" "blkuc8" "2560,874.47" "1" "1" "0")
(command "_insert" "blkuc8" "2560,874.1" "1" "1" "180")
(command "_insert" "blkuc8" "2560,874.84" "1" "1" "0")
(command "_insert" "blkuc8" "2560,874.47" "1" "1" "180")
(command "_insert" "blkuc8" "2560,875.21" "1" "1" "0")
(command "_insert" "blkuc8" "2560,874.84" "1" "1" "180")
(command "_insert" "blkuc8" "2560,875.58" "1" "1" "0")
(command "_insert" "blkuc8" "2560,875.21" "1" "1" "180")
(command "_insert" "blkuc8" "2560,875.95" "1" "1" "0")
(command "_insert" "blkuc8" "2560,875.58" "1" "1" "180")
(command "_insert" "blkuc8" "2560,876.32" "1" "1" "0")
(command "_insert" "blkuc8" "2560,875.95" "1" "1" "180")
(command "_insert" "blkuc8" "2560,876.69" "1" "1" "0")
(command "_insert" "blkuc8" "2560,876.32" "1" "1" "180")
(command "_insert" "blkuc8" "2560,877.06" "1" "1" "0")
(command "_insert" "blkuc8" "2560,876.69" "1" "1" "180")
(command "_insert" "blkuc8" "2560,877.43" "1" "1" "0")
(command "_insert" "blkuc8" "2560,877.06" "1" "1" "180")
(command "_insert" "blkuc8" "2560,877.8" "1" "1" "0")
(command "_insert" "blkuc8" "2560,877.43" "1" "1" "180")
(command "_insert" "blkuc8" "2560,878.17" "1" "1" "0")
(command "_insert" "blkuc8" "2560,877.8" "1" "1" "180")
(command "_insert" "blkuc8" "2560,878.54" "1" "1" "0")
(command "_insert" "blkuc8" "2560,878.17" "1" "1" "180")
(command "_insert" "blkuc8" "2560,878.91" "1" "1" "0")
(command "_insert" "blkuc8" "2560,878.54" "1" "1" "180")
(command "_insert" "blkuc8" "2560,879.28" "1" "1" "0")
(command "_insert" "blkuc8" "2560,878.91" "1" "1" "180")
(command "_insert" "blkuc8" "2560,879.65" "1" "1" "0")
(command "_insert" "blkuc8" "2560,879.28" "1" "1" "180")
(command "_insert" "blkuc8" "2560,880.02" "1" "1" "0")
(command "_insert" "blkuc8" "2560,879.65" "1" "1" "180")
(command "_insert" "blkuc8" "2560,880.39" "1" "1" "0")
(command "_insert" "blkuc8" "2560,880.02" "1" "1" "180")
(command "_insert" "blkuc8" "2560,880.76" "1" "1" "0")
(command "_insert" "blkuc8" "2560,880.39" "1" "1" "180")
(command "_insert" "blkuc8" "2560,881.13" "1" "1" "0")
(command "_insert" "blkuc8" "2560,880.76" "1" "1" "180")
(command "_insert" "blkuc8" "2560,881.5" "1" "1" "0")
(command "_insert" "blkuc8" "2560,881.13" "1" "1" "180")
(command "_insert" "blkuc8" "2560,881.87" "1" "1" "0")
(command "_insert" "blkuc8" "2560,881.5" "1" "1" "180")
(command "_insert" "blkuc8" "2560,882.24" "1" "1" "0")
(command "_insert" "blkuc8" "2560,881.87" "1" "1" "180")
(command "_insert" "blkuc8" "2560,882.61" "1" "1" "0")
(command "_insert" "blkuc8" "2560,882.24" "1" "1" "180")
(command "_insert" "blkuc8" "2560,882.98" "1" "1" "0")
(command "_insert" "blkuc8" "2560,882.61" "1" "1" "180")
(command "_insert" "blkuc8" "2560,883.35" "1" "1" "0")
(command "_insert" "blkuc8" "2560,882.98" "1" "1" "180")
(command "_insert" "blkuc8" "2560,883.72" "1" "1" "0")
(command "_insert" "blkuc8" "2560,883.35" "1" "1" "180")
(command "_insert" "blkuc8" "2560,884.09" "1" "1" "0")
(command "_insert" "blkuc8" "2560,883.72" "1" "1" "180")
(command "_insert" "blkuc8" "2560,884.46" "1" "1" "0")
(command "_insert" "blkuc8" "2560,884.09" "1" "1" "180")
(command "_insert" "blkuc8" "2560,884.83" "1" "1" "0")
(command "_insert" "blkuc8" "2560,884.46" "1" "1" "180")
(command "_insert" "blkuc8" "2560,885.2" "1" "1" "0")
(command "_insert" "blkuc8" "2560,884.83" "1" "1" "180")
(command "_insert" "blkuc8" "2560,885.57" "1" "1" "0")
(command "_insert" "blkuc8" "2560,885.2" "1" "1" "180")
(command "_insert" "blkuc8" "2560,885.94" "1" "1" "0")
(command "_insert" "blkuc8" "2560,885.57" "1" "1" "180")
(command "_insert" "blkuc8" "2560,886.31" "1" "1" "0")
(command "_insert" "blkuc8" "2560,885.94" "1" "1" "180")
(command "_insert" "blkuc8" "2560,886.68" "1" "1" "0")
(command "_insert" "blkuc8" "2560,886.31" "1" "1" "180")
(command "_insert" "blkuc8" "2560,887.05" "1" "1" "0")
(command "_insert" "blkuc8" "2560,886.68" "1" "1" "180")
(command "_insert" "blkuc8" "2560,887.42" "1" "1" "0")
(command "_insert" "blkuc8" "2560,887.05" "1" "1" "180")
(command "_insert" "blkuc8" "2560,887.79" "1" "1" "0")
(command "_insert" "blkuc8" "2560,887.42" "1" "1" "180")
(command "_insert" "blkuc8" "2560,888.16" "1" "1" "0")
(command "_insert" "blkuc8" "2560,887.79" "1" "1" "180")
(command "_insert" "blkuc8" "2560,888.53" "1" "1" "0")
(command "_insert" "blkuc8" "2560,888.16" "1" "1" "180")
(command "_insert" "blkuc8" "2560,888.9" "1" "1" "0")
(command "_insert" "blkuc8" "2560,888.53" "1" "1" "180")
(command "_insert" "blkuc8" "2560,889.27" "1" "1" "0")
(command "_insert" "blkuc8" "2560,888.9" "1" "1" "180")
(command "_insert" "blkuc8" "2560,889.64" "1" "1" "0")
(command "_insert" "blkuc8" "2560,889.27" "1" "1" "180")
(command "_insert" "blkuc8" "2560,890.01" "1" "1" "0")
(command "_insert" "blkuc8" "2560,889.64" "1" "1" "180")
(command "_insert" "blkuc8" "2560,890.38" "1" "1" "0")
(command "_insert" "blkuc8" "2560,890.01" "1" "1" "180")
(command "_insert" "blkuc8" "2560,890.75" "1" "1" "0")
(command "_insert" "blkuc8" "2560,890.38" "1" "1" "180")
(command "_insert" "blkuc8" "2560,891.12" "1" "1" "0")
(command "_insert" "blkuc8" "2560,890.75" "1" "1" "180")
(command "_insert" "blkuc8" "2560,891.49" "1" "1" "0")
(command "_insert" "blkuc8" "2560,891.12" "1" "1" "180")
(command "_insert" "blkuc8" "2560,891.86" "1" "1" "0")
(command "_insert" "blkuc8" "2560,891.49" "1" "1" "180")
(command "_insert" "blkuc8" "2560,892.23" "1" "1" "0")
(command "_insert" "blkuc8" "2560,891.86" "1" "1" "180")
(command "_insert" "blkuc8" "2560,892.6" "1" "1" "0")
(command "_insert" "blkuc8" "2560,892.23" "1" "1" "180")
(command "_insert" "blkuc8" "2560,892.97" "1" "1" "0")
(command "_insert" "blkuc8" "2560,892.6" "1" "1" "180")
(command "_insert" "blkuc8" "2560,893.34" "1" "1" "0")
(command "_insert" "blkuc8" "2560,892.97" "1" "1" "180")
(command "_insert" "blkuc8" "2560,893.71" "1" "1" "0")
(command "_insert" "blkuc8" "2560,893.34" "1" "1" "180")
(command "_insert" "blkuc8" "2560,894.08" "1" "1" "0")
(command "_insert" "blkuc8" "2560,893.71" "1" "1" "180")
(command "_insert" "blkuc8" "2560,894.45" "1" "1" "0")
(command "_insert" "blkuc8" "2560,894.08" "1" "1" "180")
(command "_insert" "blkuc8" "2560,894.82" "1" "1" "0")
(command "_insert" "blkuc8" "2560,894.45" "1" "1" "180")
(command "_insert" "blkuc8" "2560,895.19" "1" "1" "0")
(command "_insert" "blkuc8" "2560,894.82" "1" "1" "180")
(command "_insert" "blkuc8" "2560,895.56" "1" "1" "0")
(command "_insert" "blkuc8" "2560,895.19" "1" "1" "180")
(command "_insert" "blkuc8" "2560,895.93" "1" "1" "0")
(command "_insert" "blkuc8" "2560,895.56" "1" "1" "180")
(command "_insert" "blkuc8" "2560,896.3" "1" "1" "0")
(command "_insert" "blkuc8" "2560,895.93" "1" "1" "180")
(command "_insert" "blkuc8" "2560,896.67" "1" "1" "0")
(command "_insert" "blkuc8" "2560,896.3" "1" "1" "180")
(command "_insert" "blkuc8" "2560,897.04" "1" "1" "0")
(command "_insert" "blkuc8" "2560,896.67" "1" "1" "180")
(command "_insert" "blkuc8" "2560,897.41" "1" "1" "0")
(command "_insert" "blkuc8" "2560,897.04" "1" "1" "180")
(command "_insert" "blkuc8" "2560,897.78" "1" "1" "0")
(command "_insert" "blkuc8" "2560,897.41" "1" "1" "180")
(command "_insert" "blkuc8" "2560,898.15" "1" "1" "0")
(command "_insert" "blkuc8" "2560,897.78" "1" "1" "180")
(command "_insert" "blkuc8" "2560,898.52" "1" "1" "0")
(command "_insert" "blkuc8" "2560,898.15" "1" "1" "180")
(command "_insert" "blkuc8" "2560,898.89" "1" "1" "0")
(command "_insert" "blkuc8" "2560,898.52" "1" "1" "180")
(command "_insert" "blkuc8" "2560,899.26" "1" "1" "0")
(command "_insert" "blkuc8" "2560,898.89" "1" "1" "180")
(command "_insert" "blkuc8" "2560,899.63" "1" "1" "0")
(command "_insert" "blkuc8" "2560,899.26" "1" "1" "180")
(command "_insert" "blkuc8" "2560,900" "1" "1" "0")
(command "_insert" "blkuc8" "2560,899.63" "1" "1" "180")
(command "_insert" "blkuc8" "2560,900.37" "1" "1" "0")
(command "_insert" "blkuc8" "2560,900" "1" "1" "180")
(command "_insert" "blkuc8" "2560,900.74" "1" "1" "0")
(command "_insert" "blkuc8" "2560,900.37" "1" "1" "180")
(command "_insert" "blkuc8" "2560,901.11" "1" "1" "0")
(command "_insert" "blkuc8" "2560,900.74" "1" "1" "180")
(command "_insert" "blkuc8" "2560,901.48" "1" "1" "0")
(command "_insert" "blkuc8" "2560,901.11" "1" "1" "180")
(command "_insert" "blkuc8" "2560,901.85" "1" "1" "0")
(command "_insert" "blkuc8" "2560,901.48" "1" "1" "180")
(command "_insert" "blkuc8" "2560,902.22" "1" "1" "0")
(command "_insert" "blkuc8" "2560,901.85" "1" "1" "180")
(command "_insert" "blkuc8" "2560,902.59" "1" "1" "0")
(command "_insert" "blkuc8" "2560,902.22" "1" "1" "180")
(command "_insert" "blkuc8" "2560,902.96" "1" "1" "0")
(command "_insert" "blkuc8" "2560,902.59" "1" "1" "180")
(command "_insert" "blkuc8" "2560,903.33" "1" "1" "0")
(command "_insert" "blkuc8" "2560,902.96" "1" "1" "180")
(command "_insert" "blkuc8" "2560,903.7" "1" "1" "0")
(command "_insert" "blkuc8" "2560,903.33" "1" "1" "180")
(command "_insert" "blkuc8" "2560,904.07" "1" "1" "0")
(command "_insert" "blkuc8" "2560,903.7" "1" "1" "180")
(command "_insert" "blkuc8" "2560,904.44" "1" "1" "0")
(command "_insert" "blkuc8" "2560,904.07" "1" "1" "180")
(command "_insert" "blkuc8" "2560,904.81" "1" "1" "0")
(command "_insert" "blkuc8" "2560,904.44" "1" "1" "180")
(command "_insert" "blkuc8" "2560,905.18" "1" "1" "0")
(command "_insert" "blkuc8" "2560,904.81" "1" "1" "180")
(command "_insert" "blkuc8" "2560,905.55" "1" "1" "0")
(command "_insert" "blkuc8" "2560,905.18" "1" "1" "180")
(command "_insert" "blkuc8" "2560,905.92" "1" "1" "0")
(command "_insert" "blkuc8" "2560,905.55" "1" "1" "180")
(command "_insert" "blkuc8" "2560,906.29" "1" "1" "0")
(command "_insert" "blkuc8" "2560,905.92" "1" "1" "180")
(command "_insert" "blkuc8" "2560,906.66" "1" "1" "0")
(command "_insert" "blkuc8" "2560,906.29" "1" "1" "180")
(command "_insert" "blkuc8" "2560,907.03" "1" "1" "0")
(command "_insert" "blkuc8" "2560,906.66" "1" "1" "180")
(command "_insert" "blkuc8" "2560,907.4" "1" "1" "0")
(command "_insert" "blkuc8" "2560,907.03" "1" "1" "180")
(command "_insert" "blkuc8" "2560,907.77" "1" "1" "0")
(command "_insert" "blkuc8" "2560,907.4" "1" "1" "180")
(command "_insert" "blkuc8" "2560,908.14" "1" "1" "0")
(command "_insert" "blkuc8" "2560,907.77" "1" "1" "180")
(command "_insert" "blkuc8" "2560,908.51" "1" "1" "0")
(command "_insert" "blkuc8" "2560,908.14" "1" "1" "180")
(command "_insert" "blkuc8" "2560,908.88" "1" "1" "0")
(command "_insert" "blkuc8" "2560,908.51" "1" "1" "180")
(command "_insert" "blkuc8" "2560,909.25" "1" "1" "0")
(command "_insert" "blkuc8" "2560,908.88" "1" "1" "180")
(command "_insert" "blkuc8" "2560,909.62" "1" "1" "0")
(command "_insert" "blkuc8" "2560,909.25" "1" "1" "180")
(command "_insert" "blkuc8" "2560,909.99" "1" "1" "0")
(command "_insert" "blkuc8" "2560,909.62" "1" "1" "180")
(command "_insert" "blkuc8" "2560,910.36" "1" "1" "0")
(command "_insert" "blkuc8" "2560,909.99" "1" "1" "180")
(command "_insert" "blkuc8" "2560,910.73" "1" "1" "0")
(command "_insert" "blkuc8" "2560,910.36" "1" "1" "180")
(command "_insert" "blkuc8" "2560,911.1" "1" "1" "0")
(command "_insert" "blkuc8" "2560,910.73" "1" "1" "180")
(command "_insert" "blkuc8" "2560,911.47" "1" "1" "0")
(command "_insert" "blkuc8" "2560,911.1" "1" "1" "180")
(command "_insert" "blkuc8" "2560,911.84" "1" "1" "0")
(command "_insert" "blkuc8" "2560,911.47" "1" "1" "180")
(command "_insert" "blkuc8" "2560,912.21" "1" "1" "0")
(command "_insert" "blkuc8" "2560,911.84" "1" "1" "180")
(command "_insert" "blkuc8" "2560,912.58" "1" "1" "0")
(command "_insert" "blkuc8" "2560,912.21" "1" "1" "180")
(command "_insert" "blkuc8" "2560,912.95" "1" "1" "0")
(command "_insert" "blkuc8" "2560,912.58" "1" "1" "180")
(command "_insert" "blkuc8" "2560,913.32" "1" "1" "0")
(command "_insert" "blkuc8" "2560,912.95" "1" "1" "180")
(command "_insert" "blkuc8" "2560,913.69" "1" "1" "0")
(command "_insert" "blkuc8" "2560,913.32" "1" "1" "180")
(command "_insert" "blkuc8" "2560,914.06" "1" "1" "0")
(command "_insert" "blkuc8" "2560,913.69" "1" "1" "180")
(command "_insert" "blkuc8" "2560,914.43" "1" "1" "0")
(command "_insert" "blkuc8" "2560,914.06" "1" "1" "180")
(command "_insert" "blkuc8" "2560,914.8" "1" "1" "0")
(command "_insert" "blkuc8" "2560,914.43" "1" "1" "180")
(command "_insert" "blkuc8" "2560,915.17" "1" "1" "0")
(command "_insert" "blkuc8" "2560,914.8" "1" "1" "180")
(command "_insert" "blkuc8" "2560,915.54" "1" "1" "0")
(command "_insert" "blkuc8" "2560,915.17" "1" "1" "180")
(command "_insert" "blkuc8" "2560,915.91" "1" "1" "0")
(command "_insert" "blkuc8" "2560,915.54" "1" "1" "180")
(command "_insert" "blkuc8" "2560,916.28" "1" "1" "0")
(command "_insert" "blkuc8" "2560,915.91" "1" "1" "180")
(command "_insert" "blkuc8" "2560,916.65" "1" "1" "0")
(command "_insert" "blkuc8" "2560,916.28" "1" "1" "180")
(command "_insert" "blkuc8" "2560,917.02" "1" "1" "0")
(command "_insert" "blkuc8" "2560,916.65" "1" "1" "180")
(command "_insert" "blkuc8" "2560,917.39" "1" "1" "0")
(command "_insert" "blkuc8" "2560,917.02" "1" "1" "180")
(command "_insert" "blkuc8" "2560,917.76" "1" "1" "0")
(command "_insert" "blkuc8" "2560,917.39" "1" "1" "180")
(command "_insert" "blkuc8" "2560,918.13" "1" "1" "0")
(command "_insert" "blkuc8" "2560,917.76" "1" "1" "180")
(command "_insert" "blkuc8" "2560,918.5" "1" "1" "0")
(command "_insert" "blkuc8" "2560,918.13" "1" "1" "180")
(command "_insert" "blkuc8" "2560,918.87" "1" "1" "0")
(command "_insert" "blkuc8" "2560,918.5" "1" "1" "180")
(command "_insert" "blkuc8" "2560,919.24" "1" "1" "0")
(command "_insert" "blkuc8" "2560,918.87" "1" "1" "180")
(command "_insert" "blkuc8" "2560,919.61" "1" "1" "0")
(command "_insert" "blkuc8" "2560,919.24" "1" "1" "180")
(command "_insert" "blkuc8" "2560,919.98" "1" "1" "0")
(command "_insert" "blkuc8" "2560,919.61" "1" "1" "180")
(command "_insert" "blkuc8" "2560,920.35" "1" "1" "0")
(command "_insert" "blkuc8" "2560,919.98" "1" "1" "180")
(command "_insert" "blkuc8" "2560,920.72" "1" "1" "0")
(command "_insert" "blkuc8" "2560,920.35" "1" "1" "180")
(command "_insert" "blkuc8" "2560,921.09" "1" "1" "0")
(command "_insert" "blkuc8" "2560,920.72" "1" "1" "180")
(command "_insert" "blkuc8" "2560,921.46" "1" "1" "0")
(command "_insert" "blkuc8" "2560,921.09" "1" "1" "180")
(command "_insert" "blkuc8" "2560,921.83" "1" "1" "0")
(command "_insert" "blkuc8" "2560,921.46" "1" "1" "180")
(command "_insert" "blkuc8" "2560,922.2" "1" "1" "0")
(command "_insert" "blkuc8" "2560,921.83" "1" "1" "180")
(command "_insert" "blkuc8" "2560,922.57" "1" "1" "0")
(command "_insert" "blkuc8" "2560,922.2" "1" "1" "180")
(command "_insert" "blkuc8" "2560,922.94" "1" "1" "0")
(command "_insert" "blkuc8" "2560,922.57" "1" "1" "180")
(command "_insert" "blkuc8" "2560,923.31" "1" "1" "0")
(command "_insert" "blkuc8" "2560,922.94" "1" "1" "180")
(command "_insert" "blkuc8" "2560,923.68" "1" "1" "0")
(command "_insert" "blkuc8" "2560,923.31" "1" "1" "180")
(command "_insert" "blkuc8" "2560,924.05" "1" "1" "0")
(command "_insert" "blkuc8" "2560,923.68" "1" "1" "180")
(command "_insert" "blkuc8" "2560,924.42" "1" "1" "0")
(command "_insert" "blkuc8" "2560,924.05" "1" "1" "180")
(command "_insert" "blkuc8" "2560,924.79" "1" "1" "0")
(command "_insert" "blkuc8" "2560,924.42" "1" "1" "180")
(command "_insert" "blkuc8" "2560,925.16" "1" "1" "0")
(command "_insert" "blkuc8" "2560,924.79" "1" "1" "180")
(command "_insert" "blkuc8" "2560,925.53" "1" "1" "0")
(command "_insert" "blkuc8" "2560,925.16" "1" "1" "180")
(command "_insert" "blkuc8" "2560,925.9" "1" "1" "0")
(command "_insert" "blkuc8" "2560,925.53" "1" "1" "180")
(command "_insert" "blkuc8" "2560,926.27" "1" "1" "0")
(command "_insert" "blkuc8" "2560,925.9" "1" "1" "180")
(command "_insert" "blkuc8" "2560,926.64" "1" "1" "0")
(command "_insert" "blkuc8" "2560,926.27" "1" "1" "180")
(command "_insert" "blkuc8" "2560,927.01" "1" "1" "0")
(command "_insert" "blkuc8" "2560,926.64" "1" "1" "180")
(command "_insert" "blkuc8" "2560,927.38" "1" "1" "0")
(command "_insert" "blkuc8" "2560,927.01" "1" "1" "180")
(command "_insert" "blkuc8" "2560,927.75" "1" "1" "0")
(command "_insert" "blkuc8" "2560,927.38" "1" "1" "180")
(command "_layer" "set" "phccover" "")
(command "_rectangle" "2558.894,933.3" "2561.106,866.7")
(command "_layer" "set" "nitride" "")
(setq phc8 currobj)
(command "_layer" "set" "cover" "")
(command "_rectangle" "2558.894,836.7" "2561.106,963.3")
(command "_layer" "set" "nitride" "")
(command "_layer" "set" "text" "")
(command "_circle" "2557.944,846.7" "0.075")
(command "_circle" "2557.569,846.7" "0.15")
(command "_circle" "2557.194,846.7" "0.075")
(command "_circle" "2556.819,846.7" "0.15")
(command "_circle" "2557.944,848.7" "0.075")
(command "_circle" "2557.569,848.7" "0.075")
(command "_circle" "2557.194,848.7" "0.15")
(command "_circle" "2556.819,848.7" "0.15")
(command "_circle" "2557.944,850.7" "0.075")
(command "_circle" "2557.569,850.7" "0.15")
(command "_circle" "2557.194,850.7" "0.15")
(command "_circle" "2556.819,850.7" "0.15")
(command "_circle" "2557.944,852.7" "0.075")
(command "_circle" "2557.569,852.7" "0.075")
(command "_circle" "2557.194,852.7" "0.075")
(command "_circle" "2556.819,852.7" "0.075")
(command "_circle" "2556.444,852.7" "0.15")
(command "_circle" "2557.944,854.7" "0.075")
(command "_circle" "2557.569,854.7" "0.15")
(command "_circle" "2557.194,854.7" "0.075")
(command "_circle" "2556.819,854.7" "0.075")
(command "_circle" "2556.444,854.7" "0.15")
(command "_circle" "2557.944,856.7" "0.075")
(command "_circle" "2557.569,856.7" "0.075")
(command "_circle" "2557.194,856.7" "0.15")
(command "_circle" "2556.819,856.7" "0.075")
(command "_circle" "2556.444,856.7" "0.15")
(command "_circle" "2557.944,858.7" "0.075")
(command "_circle" "2557.569,858.7" "0.15")
(command "_circle" "2557.194,858.7" "0.15")
(command "_circle" "2556.819,858.7" "0.075")
(command "_circle" "2556.444,858.7" "0.15")
(command "_circle" "2557.944,860.7" "0.075")
(command "_circle" "2557.569,860.7" "0.075")
(command "_circle" "2557.194,860.7" "0.075")
(command "_circle" "2556.819,860.7" "0.15")
(command "_circle" "2556.444,860.7" "0.15")
(command "_circle" "2557.944,862.7" "0.075")
(command "_circle" "2557.569,862.7" "0.15")
(command "_circle" "2557.194,862.7" "0.075")
(command "_circle" "2556.819,862.7" "0.15")
(command "_circle" "2556.444,862.7" "0.15")
(command "_circle" "2557.944,864.7" "0.075")
(command "_circle" "2557.569,864.7" "0.075")
(command "_circle" "2557.194,864.7" "0.15")
(command "_circle" "2556.819,864.7" "0.15")
(command "_circle" "2556.444,864.7" "0.15")
(command "_circle" "2557.944,866.7" "0.075")
(command "_circle" "2557.569,866.7" "0.15")
(command "_circle" "2557.194,866.7" "0.15")
(command "_circle" "2556.819,866.7" "0.15")
(command "_circle" "2556.444,866.7" "0.15")
(command "_circle" "2557.944,868.7" "0.075")
(command "_circle" "2557.569,868.7" "0.075")
(command "_circle" "2557.194,868.7" "0.075")
(command "_circle" "2556.819,868.7" "0.075")
(command "_circle" "2556.444,868.7" "0.075")
(command "_circle" "2556.069,868.7" "0.15")
(command "_circle" "2557.944,870.7" "0.075")
(command "_circle" "2557.569,870.7" "0.15")
(command "_circle" "2557.194,870.7" "0.075")
(command "_circle" "2556.819,870.7" "0.075")
(command "_circle" "2556.444,870.7" "0.075")
(command "_circle" "2556.069,870.7" "0.15")
(command "_circle" "2557.944,872.7" "0.075")
(command "_circle" "2557.569,872.7" "0.075")
(command "_circle" "2557.194,872.7" "0.15")
(command "_circle" "2556.819,872.7" "0.075")
(command "_circle" "2556.444,872.7" "0.075")
(command "_circle" "2556.069,872.7" "0.15")
(command "_circle" "2557.944,874.7" "0.075")
(command "_circle" "2557.569,874.7" "0.15")
(command "_circle" "2557.194,874.7" "0.15")
(command "_circle" "2556.819,874.7" "0.075")
(command "_circle" "2556.444,874.7" "0.075")
(command "_circle" "2556.069,874.7" "0.15")
(command "_circle" "2557.944,876.7" "0.075")
(command "_circle" "2557.569,876.7" "0.075")
(command "_circle" "2557.194,876.7" "0.075")
(command "_circle" "2556.819,876.7" "0.15")
(command "_circle" "2556.444,876.7" "0.075")
(command "_circle" "2556.069,876.7" "0.15")
(command "_circle" "2557.944,878.7" "0.075")
(command "_circle" "2557.569,878.7" "0.15")
(command "_circle" "2557.194,878.7" "0.075")
(command "_circle" "2556.819,878.7" "0.15")
(command "_circle" "2556.444,878.7" "0.075")
(command "_circle" "2556.069,878.7" "0.15")
(command "_circle" "2557.944,880.7" "0.075")
(command "_circle" "2557.569,880.7" "0.075")
(command "_circle" "2557.194,880.7" "0.15")
(command "_circle" "2556.819,880.7" "0.15")
(command "_circle" "2556.444,880.7" "0.075")
(command "_circle" "2556.069,880.7" "0.15")
(command "_circle" "2557.944,882.7" "0.075")
(command "_circle" "2557.569,882.7" "0.15")
(command "_circle" "2557.194,882.7" "0.15")
(command "_circle" "2556.819,882.7" "0.15")
(command "_circle" "2556.444,882.7" "0.075")
(command "_circle" "2556.069,882.7" "0.15")
(command "_circle" "2557.944,884.7" "0.075")
(command "_circle" "2557.569,884.7" "0.075")
(command "_circle" "2557.194,884.7" "0.075")
(command "_circle" "2556.819,884.7" "0.075")
(command "_circle" "2556.444,884.7" "0.15")
(command "_circle" "2556.069,884.7" "0.15")
(command "_circle" "2557.944,886.7" "0.075")
(command "_circle" "2557.569,886.7" "0.15")
(command "_circle" "2557.194,886.7" "0.075")
(command "_circle" "2556.819,886.7" "0.075")
(command "_circle" "2556.444,886.7" "0.15")
(command "_circle" "2556.069,886.7" "0.15")
(command "_circle" "2557.944,888.7" "0.075")
(command "_circle" "2557.569,888.7" "0.075")
(command "_circle" "2557.194,888.7" "0.15")
(command "_circle" "2556.819,888.7" "0.075")
(command "_circle" "2556.444,888.7" "0.15")
(command "_circle" "2556.069,888.7" "0.15")
(command "_circle" "2557.944,890.7" "0.075")
(command "_circle" "2557.569,890.7" "0.15")
(command "_circle" "2557.194,890.7" "0.15")
(command "_circle" "2556.819,890.7" "0.075")
(command "_circle" "2556.444,890.7" "0.15")
(command "_circle" "2556.069,890.7" "0.15")
(command "_circle" "2557.944,892.7" "0.075")
(command "_circle" "2557.569,892.7" "0.075")
(command "_circle" "2557.194,892.7" "0.075")
(command "_circle" "2556.819,892.7" "0.15")
(command "_circle" "2556.444,892.7" "0.15")
(command "_circle" "2556.069,892.7" "0.15")
(command "_circle" "2557.944,894.7" "0.075")
(command "_circle" "2557.569,894.7" "0.15")
(command "_circle" "2557.194,894.7" "0.075")
(command "_circle" "2556.819,894.7" "0.15")
(command "_circle" "2556.444,894.7" "0.15")
(command "_circle" "2556.069,894.7" "0.15")
(command "_circle" "2557.944,896.7" "0.075")
(command "_circle" "2557.569,896.7" "0.075")
(command "_circle" "2557.194,896.7" "0.15")
(command "_circle" "2556.819,896.7" "0.15")
(command "_circle" "2556.444,896.7" "0.15")
(command "_circle" "2556.069,896.7" "0.15")
(command "_circle" "2557.944,898.7" "0.075")
(command "_circle" "2557.569,898.7" "0.15")
(command "_circle" "2557.194,898.7" "0.15")
(command "_circle" "2556.819,898.7" "0.15")
(command "_circle" "2556.444,898.7" "0.15")
(command "_circle" "2556.069,898.7" "0.15")
(command "_circle" "2557.944,900.7" "0.075")
(command "_circle" "2557.569,900.7" "0.075")
(command "_circle" "2557.194,900.7" "0.075")
(command "_circle" "2556.819,900.7" "0.075")
(command "_circle" "2556.444,900.7" "0.075")
(command "_circle" "2556.069,900.7" "0.075")
(command "_circle" "2555.694,900.7" "0.15")
(command "_circle" "2557.944,902.7" "0.075")
(command "_circle" "2557.569,902.7" "0.15")
(command "_circle" "2557.194,902.7" "0.075")
(command "_circle" "2556.819,902.7" "0.075")
(command "_circle" "2556.444,902.7" "0.075")
(command "_circle" "2556.069,902.7" "0.075")
(command "_circle" "2555.694,902.7" "0.15")
(command "_circle" "2557.944,904.7" "0.075")
(command "_circle" "2557.569,904.7" "0.075")
(command "_circle" "2557.194,904.7" "0.15")
(command "_circle" "2556.819,904.7" "0.075")
(command "_circle" "2556.444,904.7" "0.075")
(command "_circle" "2556.069,904.7" "0.075")
(command "_circle" "2555.694,904.7" "0.15")
(command "_circle" "2557.944,906.7" "0.075")
(command "_circle" "2557.569,906.7" "0.15")
(command "_circle" "2557.194,906.7" "0.15")
(command "_circle" "2556.819,906.7" "0.075")
(command "_circle" "2556.444,906.7" "0.075")
(command "_circle" "2556.069,906.7" "0.075")
(command "_circle" "2555.694,906.7" "0.15")
(command "_circle" "2557.944,908.7" "0.075")
(command "_circle" "2557.569,908.7" "0.075")
(command "_circle" "2557.194,908.7" "0.075")
(command "_circle" "2556.819,908.7" "0.15")
(command "_circle" "2556.444,908.7" "0.075")
(command "_circle" "2556.069,908.7" "0.075")
(command "_circle" "2555.694,908.7" "0.15")
(command "_circle" "2557.944,910.7" "0.075")
(command "_circle" "2557.569,910.7" "0.15")
(command "_circle" "2557.194,910.7" "0.075")
(command "_circle" "2556.819,910.7" "0.15")
(command "_circle" "2556.444,910.7" "0.075")
(command "_circle" "2556.069,910.7" "0.075")
(command "_circle" "2555.694,910.7" "0.15")
(command "_circle" "2557.944,912.7" "0.075")
(command "_circle" "2557.569,912.7" "0.075")
(command "_circle" "2557.194,912.7" "0.15")
(command "_circle" "2556.819,912.7" "0.15")
(command "_circle" "2556.444,912.7" "0.075")
(command "_circle" "2556.069,912.7" "0.075")
(command "_circle" "2555.694,912.7" "0.15")
(command "_circle" "2557.944,914.7" "0.075")
(command "_circle" "2557.569,914.7" "0.15")
(command "_circle" "2557.194,914.7" "0.15")
(command "_circle" "2556.819,914.7" "0.15")
(command "_circle" "2556.444,914.7" "0.075")
(command "_circle" "2556.069,914.7" "0.075")
(command "_circle" "2555.694,914.7" "0.15")
(command "_circle" "2557.944,916.7" "0.075")
(command "_circle" "2557.569,916.7" "0.075")
(command "_circle" "2557.194,916.7" "0.075")
(command "_circle" "2556.819,916.7" "0.075")
(command "_circle" "2556.444,916.7" "0.15")
(command "_circle" "2556.069,916.7" "0.075")
(command "_circle" "2555.694,916.7" "0.15")
(command "_circle" "2557.944,918.7" "0.075")
(command "_circle" "2557.569,918.7" "0.15")
(command "_circle" "2557.194,918.7" "0.075")
(command "_circle" "2556.819,918.7" "0.075")
(command "_circle" "2556.444,918.7" "0.15")
(command "_circle" "2556.069,918.7" "0.075")
(command "_circle" "2555.694,918.7" "0.15")
(command "_circle" "2557.944,920.7" "0.075")
(command "_circle" "2557.569,920.7" "0.075")
(command "_circle" "2557.194,920.7" "0.15")
(command "_circle" "2556.819,920.7" "0.075")
(command "_circle" "2556.444,920.7" "0.15")
(command "_circle" "2556.069,920.7" "0.075")
(command "_circle" "2555.694,920.7" "0.15")
(command "_circle" "2557.944,922.7" "0.075")
(command "_circle" "2557.569,922.7" "0.15")
(command "_circle" "2557.194,922.7" "0.15")
(command "_circle" "2556.819,922.7" "0.075")
(command "_circle" "2556.444,922.7" "0.15")
(command "_circle" "2556.069,922.7" "0.075")
(command "_circle" "2555.694,922.7" "0.15")
(command "_circle" "2557.944,924.7" "0.075")
(command "_circle" "2557.569,924.7" "0.075")
(command "_circle" "2557.194,924.7" "0.075")
(command "_circle" "2556.819,924.7" "0.15")
(command "_circle" "2556.444,924.7" "0.15")
(command "_circle" "2556.069,924.7" "0.075")
(command "_circle" "2555.694,924.7" "0.15")
(command "_circle" "2557.944,926.7" "0.075")
(command "_circle" "2557.569,926.7" "0.15")
(command "_circle" "2557.194,926.7" "0.075")
(command "_circle" "2556.819,926.7" "0.15")
(command "_circle" "2556.444,926.7" "0.15")
(command "_circle" "2556.069,926.7" "0.075")
(command "_circle" "2555.694,926.7" "0.15")
(command "_circle" "2557.944,928.7" "0.075")
(command "_circle" "2557.569,928.7" "0.075")
(command "_circle" "2557.194,928.7" "0.15")
(command "_circle" "2556.819,928.7" "0.15")
(command "_circle" "2556.444,928.7" "0.15")
(command "_circle" "2556.069,928.7" "0.075")
(command "_circle" "2555.694,928.7" "0.15")
(command "_circle" "2557.944,930.7" "0.075")
(command "_circle" "2557.569,930.7" "0.15")
(command "_circle" "2557.194,930.7" "0.15")
(command "_circle" "2556.819,930.7" "0.15")
(command "_circle" "2556.444,930.7" "0.15")
(command "_circle" "2556.069,930.7" "0.075")
(command "_circle" "2555.694,930.7" "0.15")
(command "_circle" "2557.944,932.7" "0.075")
(command "_circle" "2557.569,932.7" "0.075")
(command "_circle" "2557.194,932.7" "0.075")
(command "_circle" "2556.819,932.7" "0.075")
(command "_circle" "2556.444,932.7" "0.075")
(command "_circle" "2556.069,932.7" "0.15")
(command "_circle" "2555.694,932.7" "0.15")
(command "_circle" "2557.944,934.7" "0.075")
(command "_circle" "2557.569,934.7" "0.15")
(command "_circle" "2557.194,934.7" "0.075")
(command "_circle" "2556.819,934.7" "0.075")
(command "_circle" "2556.444,934.7" "0.075")
(command "_circle" "2556.069,934.7" "0.15")
(command "_circle" "2555.694,934.7" "0.15")
(command "_circle" "2557.944,936.7" "0.075")
(command "_circle" "2557.569,936.7" "0.075")
(command "_circle" "2557.194,936.7" "0.15")
(command "_circle" "2556.819,936.7" "0.075")
(command "_circle" "2556.444,936.7" "0.075")
(command "_circle" "2556.069,936.7" "0.15")
(command "_circle" "2555.694,936.7" "0.15")
(command "_circle" "2557.944,938.7" "0.075")
(command "_circle" "2557.569,938.7" "0.15")
(command "_circle" "2557.194,938.7" "0.15")
(command "_circle" "2556.819,938.7" "0.075")
(command "_circle" "2556.444,938.7" "0.075")
(command "_circle" "2556.069,938.7" "0.15")
(command "_circle" "2555.694,938.7" "0.15")
(command "_circle" "2557.944,940.7" "0.075")
(command "_circle" "2557.569,940.7" "0.075")
(command "_circle" "2557.194,940.7" "0.075")
(command "_circle" "2556.819,940.7" "0.15")
(command "_circle" "2556.444,940.7" "0.075")
(command "_circle" "2556.069,940.7" "0.15")
(command "_circle" "2555.694,940.7" "0.15")
(command "_circle" "2557.944,942.7" "0.075")
(command "_circle" "2557.569,942.7" "0.15")
(command "_circle" "2557.194,942.7" "0.075")
(command "_circle" "2556.819,942.7" "0.15")
(command "_circle" "2556.444,942.7" "0.075")
(command "_circle" "2556.069,942.7" "0.15")
(command "_circle" "2555.694,942.7" "0.15")
(command "_circle" "2557.944,944.7" "0.075")
(command "_circle" "2557.569,944.7" "0.075")
(command "_circle" "2557.194,944.7" "0.15")
(command "_circle" "2556.819,944.7" "0.15")
(command "_circle" "2556.444,944.7" "0.075")
(command "_circle" "2556.069,944.7" "0.15")
(command "_circle" "2555.694,944.7" "0.15")
(command "_circle" "2557.944,946.7" "0.075")
(command "_circle" "2557.569,946.7" "0.15")
(command "_circle" "2557.194,946.7" "0.15")
(command "_circle" "2556.819,946.7" "0.15")
(command "_circle" "2556.444,946.7" "0.075")
(command "_circle" "2556.069,946.7" "0.15")
(command "_circle" "2555.694,946.7" "0.15")
(command "_circle" "2557.944,948.7" "0.075")
(command "_circle" "2557.569,948.7" "0.075")
(command "_circle" "2557.194,948.7" "0.075")
(command "_circle" "2556.819,948.7" "0.075")
(command "_circle" "2556.444,948.7" "0.15")
(command "_circle" "2556.069,948.7" "0.15")
(command "_circle" "2555.694,948.7" "0.15")
(command "_circle" "2557.944,950.7" "0.075")
(command "_circle" "2557.569,950.7" "0.15")
(command "_circle" "2557.194,950.7" "0.075")
(command "_circle" "2556.819,950.7" "0.075")
(command "_circle" "2556.444,950.7" "0.15")
(command "_circle" "2556.069,950.7" "0.15")
(command "_circle" "2555.694,950.7" "0.15")
(command "_circle" "2557.944,952.7" "0.075")
(command "_circle" "2557.569,952.7" "0.075")
(command "_circle" "2557.194,952.7" "0.15")
(command "_circle" "2556.819,952.7" "0.075")
(command "_circle" "2556.444,952.7" "0.15")
(command "_circle" "2556.069,952.7" "0.15")
(command "_circle" "2555.694,952.7" "0.15")
(command "_circle" "2557.944,954.7" "0.075")
(command "_circle" "2557.569,954.7" "0.15")
(command "_circle" "2557.194,954.7" "0.15")
(command "_circle" "2556.819,954.7" "0.075")
(command "_circle" "2556.444,954.7" "0.15")
(command "_circle" "2556.069,954.7" "0.15")
(command "_circle" "2555.694,954.7" "0.15")
(command "_circle" "2557.944,956.7" "0.075")
(command "_circle" "2557.569,956.7" "0.075")
(command "_circle" "2557.194,956.7" "0.075")
(command "_circle" "2556.819,956.7" "0.15")
(command "_circle" "2556.444,956.7" "0.15")
(command "_circle" "2556.069,956.7" "0.15")
(command "_circle" "2555.694,956.7" "0.15")
(command "_circle" "2557.944,958.7" "0.075")
(command "_circle" "2557.569,958.7" "0.15")
(command "_circle" "2557.194,958.7" "0.075")
(command "_circle" "2556.819,958.7" "0.15")
(command "_circle" "2556.444,958.7" "0.15")
(command "_circle" "2556.069,958.7" "0.15")
(command "_circle" "2555.694,958.7" "0.15")
(command "_circle" "2557.944,960.7" "0.075")
(command "_circle" "2557.569,960.7" "0.075")
(command "_circle" "2557.194,960.7" "0.15")
(command "_circle" "2556.819,960.7" "0.15")
(command "_circle" "2556.444,960.7" "0.15")
(command "_circle" "2556.069,960.7" "0.15")
(command "_circle" "2555.694,960.7" "0.15")
(command "_circle" "2557.944,962.7" "0.075")
(command "_circle" "2557.569,962.7" "0.15")
(command "_circle" "2557.194,962.7" "0.15")
(command "_circle" "2556.819,962.7" "0.15")
(command "_circle" "2556.444,962.7" "0.15")
(command "_circle" "2556.069,962.7" "0.15")
(command "_circle" "2555.694,962.7" "0.15")
(command "_layer" "set" "nitride" "")
(command "_layer" "set" "text" "")
(command-s "_text" "2546.894,963.3" "2" "-90" "a = 370 nm" )
(sssetfirst nil (ssget "_L"))
(if (not (numberp (vl-string-search "Mac" (getvar "platform")))) (c:txtexp))
(command "_layer" "set" "nitride" "")
(command "_layer" "set" "text" "")
(command-s "_text" "2543.894,963.3" "2" "-90" "gap = 270 nm" )
(sssetfirst nil (ssget "_L"))
(if (not (numberp (vl-string-search "Mac" (getvar "platform")))) (c:txtexp))
(command "_layer" "set" "nitride" "")
(command "_layer" "set" "text" "")
(command-s "_text" "2540.894,963.3" "2" "-90" "amplitude = 137 nm" )
(sssetfirst nil (ssget "_L"))
(if (not (numberp (vl-string-search "Mac" (getvar "platform")))) (c:txtexp))
(command "_layer" "set" "nitride" "")
(command "_layer" "set" "text" "")
(command-s "_text" "2537.894,963.3" "2" "-90" "start width = 280 nm" )
(sssetfirst nil (ssget "_L"))
(if (not (numberp (vl-string-search "Mac" (getvar "platform")))) (c:txtexp))
(command "_layer" "set" "nitride" "")
(command "_layer" "set" "text" "")
(command-s "_text" "2534.894,963.3" "2" "-90" "width = 281 nm" )
(sssetfirst nil (ssget "_L"))
(if (not (numberp (vl-string-search "Mac" (getvar "platform")))) (c:txtexp))
(command "_layer" "set" "nitride" "")
(command "_layer" "set" "text" "")
(command-s "_text" "2531.894,963.3" "2" "-90" "taper: 15" )
(sssetfirst nil (ssget "_L"))
(if (not (numberp (vl-string-search "Mac" (getvar "platform")))) (c:txtexp))
(command "_layer" "set" "nitride" "")
(command "_layer" "set" "text" "")
(command-s "_text" "2528.894,963.3" "2" "-90" "nominal: 150" )
(sssetfirst nil (ssget "_L"))
(if (not (numberp (vl-string-search "Mac" (getvar "platform")))) (c:txtexp))
(command "_layer" "set" "nitride" "")
(command "_layer" "set" "indicators" "")
(setq coords (list 
(list 2480.415 940) 
(list 2480.415 920) 
(list 2460.415 900) 
(list 2480.415 880) 
(list 2480.415 860) 
(list 2480.415 900) 
(list 2480.415 887.0711) 
(list 2467.4861 900) 
(list 2480.415 912.9289) 
(list 2480.415 900)))
(apply 'command (append '("pline") coords '("c")))
(command "._fillet" "radius" "1" "._fillet" "P" (entlast))
(setq coords (list 
(list 2639.585 940) 
(list 2639.585 920) 
(list 2659.585 900) 
(list 2639.585 880) 
(list 2639.585 860) 
(list 2639.585 900) 
(list 2639.585 887.0711) 
(list 2652.5139 900) 
(list 2639.585 912.9289) 
(list 2639.585 900)))
(apply 'command (append '("pline") coords '("c")))
(command "._fillet" "radius" "1" "._fillet" "P" (entlast))
(command "_layer" "set" "holes" "")
(command "_circle" "2478.0629,914.1124" "0.5")
(command "_circle" "2475.7109,911.7603" "0.5")
(command "_circle" "2473.3588,909.4083" "0.5")
(command "_circle" "2471.0067,907.0562" "0.5")
(command "_circle" "2468.6547,904.7041" "0.5")
(command "_circle" "2466.3026,902.3521" "0.5")
(command "_circle" "2463.9505,900" "0.5")
(command "_circle" "2466.3026,897.6479" "0.5")
(command "_circle" "2468.6547,895.2959" "0.5")
(command "_circle" "2471.0067,892.9438" "0.5")
(command "_circle" "2473.3588,890.5917" "0.5")
(command "_circle" "2475.7109,888.2397" "0.5")
(command "_circle" "2478.0629,885.8876" "0.5")
(command "_circle" "2641.9371,914.1124" "0.5")
(command "_circle" "2644.2891,911.7603" "0.5")
(command "_circle" "2646.6412,909.4083" "0.5")
(command "_circle" "2648.9933,907.0562" "0.5")
(command "_circle" "2651.3453,904.7041" "0.5")
(command "_circle" "2653.6974,902.3521" "0.5")
(command "_circle" "2656.0495,900" "0.5")
(command "_circle" "2653.6974,897.6479" "0.5")
(command "_circle" "2651.3453,895.2959" "0.5")
(command "_circle" "2648.9933,892.9438" "0.5")
(command "_circle" "2646.6412,890.5917" "0.5")
(command "_circle" "2644.2891,888.2397" "0.5")
(command "_circle" "2641.9371,885.8876" "0.5")
(command "_layer" "set" "nitride" "")
(command "_block" "blkcoupler8" "2560,900" coupler8 "")
(command "_insert" "blkcoupler8" "2560,900" "1" "1" "0")
(command "_insert" "blkcoupler8" "2560,900" "1" "1" "180")
(command "_block" "blksinglenanobeam8" "2560,900" singlenanobeam8 "")
(command "_insert" "blksinglenanobeam8" "2560,900" "1" "1" "0")
(command "_insert" "blksinglenanobeam8" "2560,900" "1" "1" "180")
(command "_block" "blkanglednodearray8" "2560,900" anglednodearray8 "")
(command "_insert" "blkanglednodearray8" "2560,900" "1" "1" "0")
(command "_insert" "blkanglednodearray8" "2560,900" "1" "1" "180")
(command "_block" "blkcooledsinglenanobeam8" "2560,900" cooledsinglenanobeam8 "")
(command "_insert" "blkcooledsinglenanobeam8" "2560,900" "1" "1" "0")
(command "_insert" "blkcooledsinglenanobeam8" "2560,900" "1" "1" "180")
(command "_block" "blkyjunction8" "2560,900" yjunction8 "")
(command "_insert" "blkyjunction8" "2560,900" "1" "1" "0")
(command "_insert" "blkyjunction8" "2560,900" "1" "1" "180")
; DRAWING BULGING VEE GROOVE
(command "_layer" "set" "vgroove" "")
(setq coords (list 
(list 2485.415 -605) 
(list 2485.415 0) 
(list 2485.415 0) 
(list 2485.415 1800) 
(list 2485.415 1800) 
(list 2485.415 2405) 
(list 2634.585 2405) 
(list 2634.585 1800) 
(list 2634.585 1800) 
(list 2634.585 0) 
(list 2634.585 0) 
(list 2634.585 -605)))
(apply 'command (append '("pline") coords '("c")))
(command "._fillet" "radius" "0" "._fillet" "P" (entlast))
(command "_layer" "set" "window" "")
(command "_rectangle" "2485.415,-1935" "2634.585,-600")
(command "_rectangle" "2485.415,2400" "2634.585,5300")
(command "_layer" "set" "grid" "")
(command "_rectangle" "2486.415,-1934" "2509.9433,-1909.2133")
(command "_array" "last" "" "R" "75" "3" "25.7867" "24.5283")
(command "_rectangle" "2561,-1934" "2584.5283,-1909.2133")
(command "_array" "last" "" "R" "75" "3" "25.7867" "24.5283")
(command "_rectangle" "2486.415,1" "2509.9433,25.7")
(command "_array" "last" "" "R" "70" "3" "25.7" "24.5283")
(command "_rectangle" "2561,1" "2584.5283,25.7")
(command "_array" "last" "" "R" "70" "3" "25.7" "24.5283")
(command "_rectangle" "2486.415,1801" "2509.9433,1825.9185")
(command "_array" "last" "" "R" "135" "3" "25.9185" "24.5283")
(command "_rectangle" "2561,1801" "2584.5283,1825.9185")
(command "_array" "last" "" "R" "135" "3" "25.9185" "24.5283")
(command "_layer" "set" "vgrooveFDA" "")
(command "_rectangle" "2634.585,-2233" "2485.415,-1933")
(command "_layer" "set" "nitride" "")
(command "_layer" "set" "holes" "")
(command "_circle" "2637.085,331.5" "0.5")
(command "_array" "last" "" "R" "379" "1" "3" "2.5")
(command "_circle" "2482.915,331.5" "0.5")
(command "_array" "last" "" "R" "379" "1" "3" "-2.5")
(command "_layer" "set" "nitride" "")
(command "_layer" "set" "window" "")
(command "_layer" "set" "window" "")
(command "_rectangle" "2639.585,0" "2800.415,1800")
(command "._fillet" "radius" "20" "._fillet" "P" (entlast))
(command "_layer" "set" "grid" "")
(command "_rectangle" "2640.585,1" "2662.4179,25.7")
(command "_array" "last" "" "R" "70" "7" "25.7" "22.8329")
(command "_layer" "set" "nitride" "")
; DRAWING REGION LAYER
(command "_layer" "set" "regionLayer8" "")
(command "_rectangle" "2480,-460" "2640,2260")
(command "_layer" "set" "nitride" "")
(setq coupler8 nil)
(setq singlenanobeam8 nil)
(setq anglednodearray8 nil)
(setq cooledsinglenanobeam8 nil)
(setq yjunction8 nil)
; DEVICE #9
(command "_layer" "set" "window" "")
(command "_circle" "2792.915,-415" "5")
(command "_circle" "2792.915,-402.5" "5")
(command "_circle" "2792.915,-390" "5")
(command "_circle" "2792.915,-377.5" "5")
(command "_circle" "2780.415,-415" "5")
(command "_circle" "2780.415,-402.5" "5")
(command "_circle" "2780.415,-390" "5")
(command "_circle" "2780.415,-377.5" "5")
(command "_circle" "2767.915,-415" "5")
(command "_layer" "set" "nitride" "")
(setq currobj nil)
(setq currobj (ssadd))
; DRAWING COUPLER
(setq coords (list 
(list 2880.0615 -415) 
(list 2880.0615 -413) 
(list 2953.585 -413) 
(list 2953.585 -413) 
(list 2953.9677 -413.0761) 
(list 2954.2921 -413.2929) 
(list 2954.5089 -413.6173) 
(list 2954.585 -414) 
(list 2954.585 -411.8) 
(list 2954.585 -411.8) 
(list 2954.5089 -412.1827) 
(list 2954.2921 -412.5071) 
(list 2953.9677 -412.7239) 
(list 2953.585 -412.8) 
(list 2880.0615 -412.8) 
(list 2880.0615 -410.8) 
(list 2879.9385 -410.8) 
(list 2879.9385 -412.8) 
(list 2806.415 -412.8) 
(list 2806.0323 -412.7239) 
(list 2805.7079 -412.5071) 
(list 2805.4911 -412.1827) 
(list 2805.415 -411.8) 
(list 2805.415 -411.8) 
(list 2805.415 -414) 
(list 2805.4911 -413.6173) 
(list 2805.7079 -413.2929) 
(list 2806.0323 -413.0761) 
(list 2806.415 -413) 
(list 2806.415 -413) 
(list 2879.9385 -413) 
(list 2879.9385 -415)))
(apply 'command (append '("pline") coords '("c")))
(setq currobj (ssadd (entlast) currobj))
(command "._fillet" "radius" "0.3" "._fillet" "P" (entlast))
(command "_layer" "set" "holes" "")
(command "_circle" "2880,-412.9" "0.113")
(setq currobj (ssadd (entlast) currobj))
(command "_layer" "set" "nitride" "")
(command "_layer" "set" "text" "")
(command "_circle" "2879.2,-415" "0.075")
(command "_circle" "2879.2,-414.7" "0.075")
(command "_circle" "2879.2,-414.4" "0.075")
(command "_circle" "2878.9,-415" "0.075")
(command "_circle" "2878.9,-414.7" "0.075")
(command "_circle" "2878.9,-414.4" "0.075")
(command "_circle" "2878.6,-415" "0.075")
(command "_circle" "2878.6,-414.7" "0.075")
(command "_circle" "2878.6,-414.4" "0.075")
(command "_layer" "set" "nitride" "")
(command "_layer" "set" "prebias" "")
(command "_rectangle" "2805.415,-414" "2954.585,-411.8")
(setq currobj (ssadd (entlast) currobj))
(command "_rectangle" "2879.9385,-415" "2880.0615,-410.8")
(setq currobj (ssadd (entlast) currobj))
(command "_layer" "set" "nitride" "")
(setq coupler9 currobj)
(setq currobj nil)
(setq currobj (ssadd))
; DRAWING SINGLE NANOBEAM
(setq coords (list 
(list 2880.0615 -410.8) 
(list 2880.0615 -409.1417) 
(list 2880.0615 -407.4833) 
(list 2880.0615 -405.825) 
(list 2880.0615 -404.1667) 
(list 2880.0615 -402.5083) 
(list 2880.0615 -400.85) 
(list 2880.0615 -399.1917) 
(list 2880.0615 -397.5333) 
(list 2880.0616 -395.875) 
(list 2880.0616 -394.2167) 
(list 2880.0616 -392.5583) 
(list 2880.0616 -390.9) 
(list 2880.0617 -389.2417) 
(list 2880.0617 -387.5833) 
(list 2880.0617 -385.925) 
(list 2880.0618 -384.2667) 
(list 2880.0619 -382.6083) 
(list 2880.0619 -380.95) 
(list 2880.062 -379.2917) 
(list 2880.0621 -377.6333) 
(list 2880.0622 -375.975) 
(list 2880.0623 -374.3167) 
(list 2880.0624 -372.6583) 
(list 2880.0625 -371) 
(list 2880.0626 -369.3417) 
(list 2880.0628 -367.6833) 
(list 2880.0629 -366.025) 
(list 2880.0631 -364.3667) 
(list 2880.0632 -362.7083) 
(list 2880.0634 -361.05) 
(list 2880.0636 -359.3917) 
(list 2880.0638 -357.7333) 
(list 2880.0641 -356.075) 
(list 2880.0643 -354.4167) 
(list 2880.0646 -352.7583) 
(list 2880.0648 -351.1) 
(list 2880.0651 -349.4417) 
(list 2880.0654 -347.7833) 
(list 2880.0657 -346.125) 
(list 2880.0661 -344.4667) 
(list 2880.0664 -342.8083) 
(list 2880.0668 -341.15) 
(list 2880.0672 -339.4917) 
(list 2880.0676 -337.8333) 
(list 2880.068 -336.175) 
(list 2880.0685 -334.5167) 
(list 2880.0689 -332.8583) 
(list 2880.0694 -331.2) 
(list 2880.0699 -329.5417) 
(list 2880.0704 -327.8833) 
(list 2880.071 -326.225) 
(list 2880.0715 -324.5667) 
(list 2880.0721 -322.9083) 
(list 2880.0728 -321.25) 
(list 2880.0734 -319.5917) 
(list 2880.0741 -317.9333) 
(list 2880.0747 -316.275) 
(list 2880.0754 -314.6167) 
(list 2880.0762 -312.9583) 
(list 2880.0769 -311.3) 
(list 2880.0777 -309.6417) 
(list 2880.0785 -307.9833) 
(list 2880.0794 -306.325) 
(list 2880.0802 -304.6667) 
(list 2880.0811 -303.0083) 
(list 2880.082 -301.35) 
(list 2880.083 -299.6917) 
(list 2880.084 -298.0333) 
(list 2880.085 -296.375) 
(list 2880.086 -294.7167) 
(list 2880.0871 -293.0583) 
(list 2880.0882 -291.4) 
(list 2880.0893 -289.7417) 
(list 2880.0905 -288.0833) 
(list 2880.0917 -286.425) 
(list 2880.0929 -284.7667) 
(list 2880.0941 -283.1083) 
(list 2880.0954 -281.45) 
(list 2880.0967 -279.7917) 
(list 2880.0981 -278.1333) 
(list 2880.0995 -276.475) 
(list 2880.1009 -274.8167) 
(list 2880.1024 -273.1583) 
(list 2880.1039 -271.5) 
(list 2880.1054 -269.8417) 
(list 2880.107 -268.1833) 
(list 2880.1086 -266.525) 
(list 2880.1102 -264.8667) 
(list 2880.1119 -263.2083) 
(list 2880.1136 -261.55) 
(list 2880.1154 -259.8917) 
(list 2880.1172 -258.2333) 
(list 2880.119 -256.575) 
(list 2880.1209 -254.9167) 
(list 2880.1228 -253.2583) 
(list 2880.1247 -251.6) 
(list 2880.1267 -249.9417) 
(list 2880.1288 -248.2833) 
(list 2880.1308 -246.625) 
(list 2880.133 -244.9667) 
(list 2880.1351 -243.3083) 
(list 2880.1373 -241.65) 
(list 2880.1396 -239.9917) 
(list 2880.1419 -238.3333) 
(list 2880.1442 -236.675) 
(list 2880.1466 -235.0167) 
(list 2880.1491 -233.3583) 
(list 2880.1515 -231.7) 
(list 2880.1541 -230.0417) 
(list 2880.1566 -228.3833) 
(list 2880.1592 -226.725) 
(list 2880.1619 -225.0667) 
(list 2880.1646 -223.4083) 
(list 2880.1674 -221.75) 
(list 2880.1702 -220.0917) 
(list 2880.1731 -218.4333) 
(list 2880.176 -216.775) 
(list 2880.1789 -215.1167) 
(list 2880.1819 -213.4583) 
(list 2880.185 -211.8) 
(list 2879.815 -211.8) 
(list 2879.8181 -213.4583) 
(list 2879.8211 -215.1167) 
(list 2879.824 -216.775) 
(list 2879.8269 -218.4333) 
(list 2879.8298 -220.0917) 
(list 2879.8326 -221.75) 
(list 2879.8354 -223.4083) 
(list 2879.8381 -225.0667) 
(list 2879.8408 -226.725) 
(list 2879.8434 -228.3833) 
(list 2879.8459 -230.0417) 
(list 2879.8485 -231.7) 
(list 2879.8509 -233.3583) 
(list 2879.8534 -235.0167) 
(list 2879.8558 -236.675) 
(list 2879.8581 -238.3333) 
(list 2879.8604 -239.9917) 
(list 2879.8627 -241.65) 
(list 2879.8649 -243.3083) 
(list 2879.867 -244.9667) 
(list 2879.8692 -246.625) 
(list 2879.8712 -248.2833) 
(list 2879.8733 -249.9417) 
(list 2879.8753 -251.6) 
(list 2879.8772 -253.2583) 
(list 2879.8791 -254.9167) 
(list 2879.881 -256.575) 
(list 2879.8828 -258.2333) 
(list 2879.8846 -259.8917) 
(list 2879.8864 -261.55) 
(list 2879.8881 -263.2083) 
(list 2879.8898 -264.8667) 
(list 2879.8914 -266.525) 
(list 2879.893 -268.1833) 
(list 2879.8946 -269.8417) 
(list 2879.8961 -271.5) 
(list 2879.8976 -273.1583) 
(list 2879.8991 -274.8167) 
(list 2879.9005 -276.475) 
(list 2879.9019 -278.1333) 
(list 2879.9033 -279.7917) 
(list 2879.9046 -281.45) 
(list 2879.9059 -283.1083) 
(list 2879.9071 -284.7667) 
(list 2879.9083 -286.425) 
(list 2879.9095 -288.0833) 
(list 2879.9107 -289.7417) 
(list 2879.9118 -291.4) 
(list 2879.9129 -293.0583) 
(list 2879.914 -294.7167) 
(list 2879.915 -296.375) 
(list 2879.916 -298.0333) 
(list 2879.917 -299.6917) 
(list 2879.918 -301.35) 
(list 2879.9189 -303.0083) 
(list 2879.9198 -304.6667) 
(list 2879.9206 -306.325) 
(list 2879.9215 -307.9833) 
(list 2879.9223 -309.6417) 
(list 2879.9231 -311.3) 
(list 2879.9238 -312.9583) 
(list 2879.9246 -314.6167) 
(list 2879.9253 -316.275) 
(list 2879.9259 -317.9333) 
(list 2879.9266 -319.5917) 
(list 2879.9272 -321.25) 
(list 2879.9279 -322.9083) 
(list 2879.9285 -324.5667) 
(list 2879.929 -326.225) 
(list 2879.9296 -327.8833) 
(list 2879.9301 -329.5417) 
(list 2879.9306 -331.2) 
(list 2879.9311 -332.8583) 
(list 2879.9315 -334.5167) 
(list 2879.932 -336.175) 
(list 2879.9324 -337.8333) 
(list 2879.9328 -339.4917) 
(list 2879.9332 -341.15) 
(list 2879.9336 -342.8083) 
(list 2879.9339 -344.4667) 
(list 2879.9343 -346.125) 
(list 2879.9346 -347.7833) 
(list 2879.9349 -349.4417) 
(list 2879.9352 -351.1) 
(list 2879.9354 -352.7583) 
(list 2879.9357 -354.4167) 
(list 2879.9359 -356.075) 
(list 2879.9362 -357.7333) 
(list 2879.9364 -359.3917) 
(list 2879.9366 -361.05) 
(list 2879.9368 -362.7083) 
(list 2879.9369 -364.3667) 
(list 2879.9371 -366.025) 
(list 2879.9372 -367.6833) 
(list 2879.9374 -369.3417) 
(list 2879.9375 -371) 
(list 2879.9376 -372.6583) 
(list 2879.9377 -374.3167) 
(list 2879.9378 -375.975) 
(list 2879.9379 -377.6333) 
(list 2879.938 -379.2917) 
(list 2879.9381 -380.95) 
(list 2879.9381 -382.6083) 
(list 2879.9382 -384.2667) 
(list 2879.9383 -385.925) 
(list 2879.9383 -387.5833) 
(list 2879.9383 -389.2417) 
(list 2879.9384 -390.9) 
(list 2879.9384 -392.5583) 
(list 2879.9384 -394.2167) 
(list 2879.9384 -395.875) 
(list 2879.9385 -397.5333) 
(list 2879.9385 -399.1917) 
(list 2879.9385 -400.85) 
(list 2879.9385 -402.5083) 
(list 2879.9385 -404.1667) 
(list 2879.9385 -405.825) 
(list 2879.9385 -407.4833) 
(list 2879.9385 -409.1417) 
(list 2879.9385 -410.8)))
(apply 'command (append '("pline") coords '("c")))
(setq currobj (ssadd (entlast) currobj))
(command "_layer" "set" "prebias" "")
(command "_rectangle" "2879.815,-410.8" "2880.185,-211.8")
(setq currobj (ssadd (entlast) currobj))
(command "_layer" "set" "nitride" "")
(setq singlenanobeam9 currobj)
(setq currobj nil)
(setq currobj (ssadd))
; DRAWING NODE ARRAY
(setq coords (list 
(list 2880.185 -211.8) 
(list 2880.5625 -201.8) 
(list 2880.5625 -201.8) 
(list 2880.5625 -200.8) 
(list 2954.585 -212.6864) 
(list 2954.585 -207.7434) 
(list 2880.5625 -197.357) 
(list 2880.5625 -196.357) 
(list 2880.5625 -196.357) 
(list 2880.2625 -186.357) 
(list 2879.7375 -186.357) 
(list 2879.4375 -196.357) 
(list 2879.4375 -196.357) 
(list 2879.4375 -197.357) 
(list 2805.415 -207.7434) 
(list 2805.415 -212.6864) 
(list 2879.4375 -200.8) 
(list 2879.4375 -201.8) 
(list 2879.4375 -201.8) 
(list 2879.815 -211.8)))
(apply 'command (append '("pline") coords '("c")))
(setq currobj (ssadd (entlast) currobj))
(command "_layer" "set" "prebias" "")
(setq coords (list 
(list 2879.4375 -212.6864) 
(list 2879.4375 -200.8) 
(list 2805.415 -212.6864) 
(list 2805.415 -207.7434) 
(list 2879.4375 -197.357) 
(list 2879.4375 -186.357) 
(list 2880.5625 -186.357) 
(list 2880.5625 -197.357) 
(list 2954.585 -207.7434) 
(list 2954.585 -212.6864) 
(list 2880.5625 -200.8) 
(list 2880.5625 -212.6864)))
(apply 'command (append '("pline") coords '("c")))
(setq currobj (ssadd (entlast) currobj))
(command "_layer" "set" "nitride" "")
(command "_layer" "set" "fda1" "")
(setq coords (list 
(list 2880.5625 -200.657) 
(list 2954.585 -212.5434) 
(list 2954.585 -212.3664) 
(list 2880.5625 -200.58)))
(apply 'command (append '("pline") coords '("c")))
(setq currobj (ssadd (entlast) currobj))
(setq coords (list 
(list 2880.5625 -200.437) 
(list 2954.585 -212.2234) 
(list 2954.585 -212.0464) 
(list 2880.5625 -200.36)))
(apply 'command (append '("pline") coords '("c")))
(setq currobj (ssadd (entlast) currobj))
(setq coords (list 
(list 2880.5625 -200.217) 
(list 2954.585 -211.9034) 
(list 2954.585 -211.7264) 
(list 2880.5625 -200.14)))
(apply 'command (append '("pline") coords '("c")))
(setq currobj (ssadd (entlast) currobj))
(setq coords (list 
(list 2880.5625 -199.997) 
(list 2954.585 -211.5834) 
(list 2954.585 -211.4064) 
(list 2880.5625 -199.92)))
(apply 'command (append '("pline") coords '("c")))
(setq currobj (ssadd (entlast) currobj))
(setq coords (list 
(list 2880.5625 -199.777) 
(list 2954.585 -211.2634) 
(list 2954.585 -211.0864) 
(list 2880.5625 -199.7)))
(apply 'command (append '("pline") coords '("c")))
(setq currobj (ssadd (entlast) currobj))
(setq coords (list 
(list 2880.5625 -199.557) 
(list 2954.585 -210.9434) 
(list 2954.585 -210.7664) 
(list 2880.5625 -199.48)))
(apply 'command (append '("pline") coords '("c")))
(setq currobj (ssadd (entlast) currobj))
(setq coords (list 
(list 2880.5625 -199.337) 
(list 2954.585 -210.6234) 
(list 2954.585 -210.4464) 
(list 2880.5625 -199.26)))
(apply 'command (append '("pline") coords '("c")))
(setq currobj (ssadd (entlast) currobj))
(setq coords (list 
(list 2880.5625 -199.117) 
(list 2954.585 -210.3034) 
(list 2954.585 -210.1264) 
(list 2880.5625 -199.04)))
(apply 'command (append '("pline") coords '("c")))
(setq currobj (ssadd (entlast) currobj))
(setq coords (list 
(list 2880.5625 -198.897) 
(list 2954.585 -209.9834) 
(list 2954.585 -209.8064) 
(list 2880.5625 -198.82)))
(apply 'command (append '("pline") coords '("c")))
(setq currobj (ssadd (entlast) currobj))
(setq coords (list 
(list 2880.5625 -198.677) 
(list 2954.585 -209.6634) 
(list 2954.585 -209.4864) 
(list 2880.5625 -198.6)))
(apply 'command (append '("pline") coords '("c")))
(setq currobj (ssadd (entlast) currobj))
(setq coords (list 
(list 2880.5625 -198.457) 
(list 2954.585 -209.3434) 
(list 2954.585 -209.1664) 
(list 2880.5625 -198.38)))
(apply 'command (append '("pline") coords '("c")))
(setq currobj (ssadd (entlast) currobj))
(setq coords (list 
(list 2880.5625 -198.237) 
(list 2954.585 -209.0234) 
(list 2954.585 -208.8464) 
(list 2880.5625 -198.16)))
(apply 'command (append '("pline") coords '("c")))
(setq currobj (ssadd (entlast) currobj))
(setq coords (list 
(list 2880.5625 -198.017) 
(list 2954.585 -208.7034) 
(list 2954.585 -208.5264) 
(list 2880.5625 -197.94)))
(apply 'command (append '("pline") coords '("c")))
(setq currobj (ssadd (entlast) currobj))
(setq coords (list 
(list 2880.5625 -197.797) 
(list 2954.585 -208.3834) 
(list 2954.585 -208.2064) 
(list 2880.5625 -197.72)))
(apply 'command (append '("pline") coords '("c")))
(setq currobj (ssadd (entlast) currobj))
(setq coords (list 
(list 2880.5625 -197.577) 
(list 2954.585 -208.0634) 
(list 2954.585 -207.8864) 
(list 2880.5625 -197.5)))
(apply 'command (append '("pline") coords '("c")))
(setq currobj (ssadd (entlast) currobj))
(setq coords (list 
(list 2879.4375 -197.5) 
(list 2805.415 -207.8864) 
(list 2805.415 -208.0634) 
(list 2879.4375 -197.577)))
(apply 'command (append '("pline") coords '("c")))
(setq currobj (ssadd (entlast) currobj))
(setq coords (list 
(list 2879.4375 -197.72) 
(list 2805.415 -208.2064) 
(list 2805.415 -208.3834) 
(list 2879.4375 -197.797)))
(apply 'command (append '("pline") coords '("c")))
(setq currobj (ssadd (entlast) currobj))
(setq coords (list 
(list 2879.4375 -197.94) 
(list 2805.415 -208.5264) 
(list 2805.415 -208.7034) 
(list 2879.4375 -198.017)))
(apply 'command (append '("pline") coords '("c")))
(setq currobj (ssadd (entlast) currobj))
(setq coords (list 
(list 2879.4375 -198.16) 
(list 2805.415 -208.8464) 
(list 2805.415 -209.0234) 
(list 2879.4375 -198.237)))
(apply 'command (append '("pline") coords '("c")))
(setq currobj (ssadd (entlast) currobj))
(setq coords (list 
(list 2879.4375 -198.38) 
(list 2805.415 -209.1664) 
(list 2805.415 -209.3434) 
(list 2879.4375 -198.457)))
(apply 'command (append '("pline") coords '("c")))
(setq currobj (ssadd (entlast) currobj))
(setq coords (list 
(list 2879.4375 -198.6) 
(list 2805.415 -209.4864) 
(list 2805.415 -209.6634) 
(list 2879.4375 -198.677)))
(apply 'command (append '("pline") coords '("c")))
(setq currobj (ssadd (entlast) currobj))
(setq coords (list 
(list 2879.4375 -198.82) 
(list 2805.415 -209.8064) 
(list 2805.415 -209.9834) 
(list 2879.4375 -198.897)))
(apply 'command (append '("pline") coords '("c")))
(setq currobj (ssadd (entlast) currobj))
(setq coords (list 
(list 2879.4375 -199.04) 
(list 2805.415 -210.1264) 
(list 2805.415 -210.3034) 
(list 2879.4375 -199.117)))
(apply 'command (append '("pline") coords '("c")))
(setq currobj (ssadd (entlast) currobj))
(setq coords (list 
(list 2879.4375 -199.26) 
(list 2805.415 -210.4464) 
(list 2805.415 -210.6234) 
(list 2879.4375 -199.337)))
(apply 'command (append '("pline") coords '("c")))
(setq currobj (ssadd (entlast) currobj))
(setq coords (list 
(list 2879.4375 -199.48) 
(list 2805.415 -210.7664) 
(list 2805.415 -210.9434) 
(list 2879.4375 -199.557)))
(apply 'command (append '("pline") coords '("c")))
(setq currobj (ssadd (entlast) currobj))
(setq coords (list 
(list 2879.4375 -199.7) 
(list 2805.415 -211.0864) 
(list 2805.415 -211.2634) 
(list 2879.4375 -199.777)))
(apply 'command (append '("pline") coords '("c")))
(setq currobj (ssadd (entlast) currobj))
(setq coords (list 
(list 2879.4375 -199.92) 
(list 2805.415 -211.4064) 
(list 2805.415 -211.5834) 
(list 2879.4375 -199.997)))
(apply 'command (append '("pline") coords '("c")))
(setq currobj (ssadd (entlast) currobj))
(setq coords (list 
(list 2879.4375 -200.14) 
(list 2805.415 -211.7264) 
(list 2805.415 -211.9034) 
(list 2879.4375 -200.217)))
(apply 'command (append '("pline") coords '("c")))
(setq currobj (ssadd (entlast) currobj))
(setq coords (list 
(list 2879.4375 -200.36) 
(list 2805.415 -212.0464) 
(list 2805.415 -212.2234) 
(list 2879.4375 -200.437)))
(apply 'command (append '("pline") coords '("c")))
(setq currobj (ssadd (entlast) currobj))
(setq coords (list 
(list 2879.4375 -200.58) 
(list 2805.415 -212.3664) 
(list 2805.415 -212.5434) 
(list 2879.4375 -200.657)))
(apply 'command (append '("pline") coords '("c")))
(setq currobj (ssadd (entlast) currobj))
(command "_layer" "set" "nitride" "")
(command "_layer" "set" "text" "")
(command "_circle" "2878.985,-211.8" "0.075")
(command "_circle" "2878.985,-211.5" "0.075")
(command "_circle" "2878.985,-211.2" "0.075")
(command "_circle" "2878.985,-210.9" "0.075")
(command "_circle" "2878.985,-210.6" "0.075")
(command "_circle" "2878.685,-211.8" "0.075")
(command "_circle" "2878.685,-211.5" "0.075")
(command "_circle" "2878.685,-211.2" "0.075")
(command "_circle" "2878.685,-210.9" "0.075")
(command "_circle" "2878.685,-210.6" "0.075")
(command "_circle" "2878.385,-211.8" "0.075")
(command "_circle" "2878.385,-211.5" "0.075")
(command "_circle" "2878.385,-211.2" "0.075")
(command "_circle" "2878.385,-210.9" "0.075")
(command "_circle" "2878.385,-210.6" "0.075")
(command "_circle" "2878.085,-211.8" "0.075")
(command "_circle" "2878.085,-211.5" "0.075")
(command "_circle" "2878.085,-211.2" "0.075")
(command "_circle" "2878.085,-210.9" "0.075")
(command "_circle" "2878.085,-210.6" "0.075")
(command "_circle" "2877.785,-211.8" "0.075")
(command "_circle" "2877.785,-211.5" "0.075")
(command "_circle" "2877.785,-211.2" "0.075")
(command "_circle" "2877.785,-210.9" "0.075")
(command "_circle" "2877.785,-210.6" "0.075")
(command "_layer" "set" "nitride" "")
(setq anglednodearray9 currobj)
(setq currobj nil)
(setq currobj (ssadd))
; DRAWING COOLED SINGLE NANOBEAM
(setq coords (list 
(list 2880.2625 -186.357) 
(list 2880.2625 -181.357) 
(list 2879.7375 -181.357) 
(list 2879.7375 -186.357)))
(apply 'command (append '("pline") coords '("c")))
(setq currobj (ssadd (entlast) currobj))
(command "_layer" "set" "prebias" "")
(command "_rectangle" "2879.7375,-186.357" "2880.2625,-181.357")
(setq currobj (ssadd (entlast) currobj))
(command "_layer" "set" "nitride" "")
(setq coords (list 
(list 2880.2625 -181.357) 
(list 2880.5625 -171.357) 
(list 2880.5625 -171.357) 
(list 2880.5625 -170.357) 
(list 2954.585 -171.107) 
(list 2954.585 -166.164) 
(list 2880.5625 -166.914) 
(list 2880.5625 -165.914) 
(list 2880.5625 -165.914) 
(list 2880.2625 -155.914) 
(list 2879.7375 -155.914) 
(list 2879.4375 -165.914) 
(list 2879.4375 -165.914) 
(list 2879.4375 -166.914) 
(list 2805.415 -166.164) 
(list 2805.415 -171.107) 
(list 2879.4375 -170.357) 
(list 2879.4375 -171.357) 
(list 2879.4375 -171.357) 
(list 2879.7375 -181.357)))
(apply 'command (append '("pline") coords '("c")))
(setq currobj (ssadd (entlast) currobj))
(command "_layer" "set" "prebias" "")
(setq coords (list 
(list 2879.4375 -181.357) 
(list 2879.4375 -170.357) 
(list 2805.415 -171.107) 
(list 2805.415 -166.164) 
(list 2879.4375 -166.914) 
(list 2879.4375 -155.914) 
(list 2880.5625 -155.914) 
(list 2880.5625 -166.914) 
(list 2954.585 -166.164) 
(list 2954.585 -171.107) 
(list 2880.5625 -170.357) 
(list 2880.5625 -181.357)))
(apply 'command (append '("pline") coords '("c")))
(setq currobj (ssadd (entlast) currobj))
(command "_layer" "set" "nitride" "")
(command "_layer" "set" "fda1" "")
(setq coords (list 
(list 2880.5625 -170.214) 
(list 2954.585 -170.964) 
(list 2954.585 -170.787) 
(list 2880.5625 -170.137)))
(apply 'command (append '("pline") coords '("c")))
(setq currobj (ssadd (entlast) currobj))
(setq coords (list 
(list 2880.5625 -169.994) 
(list 2954.585 -170.644) 
(list 2954.585 -170.467) 
(list 2880.5625 -169.917)))
(apply 'command (append '("pline") coords '("c")))
(setq currobj (ssadd (entlast) currobj))
(setq coords (list 
(list 2880.5625 -169.774) 
(list 2954.585 -170.324) 
(list 2954.585 -170.147) 
(list 2880.5625 -169.697)))
(apply 'command (append '("pline") coords '("c")))
(setq currobj (ssadd (entlast) currobj))
(setq coords (list 
(list 2880.5625 -169.554) 
(list 2954.585 -170.004) 
(list 2954.585 -169.827) 
(list 2880.5625 -169.477)))
(apply 'command (append '("pline") coords '("c")))
(setq currobj (ssadd (entlast) currobj))
(setq coords (list 
(list 2880.5625 -169.334) 
(list 2954.585 -169.684) 
(list 2954.585 -169.507) 
(list 2880.5625 -169.257)))
(apply 'command (append '("pline") coords '("c")))
(setq currobj (ssadd (entlast) currobj))
(setq coords (list 
(list 2880.5625 -169.114) 
(list 2954.585 -169.364) 
(list 2954.585 -169.187) 
(list 2880.5625 -169.037)))
(apply 'command (append '("pline") coords '("c")))
(setq currobj (ssadd (entlast) currobj))
(setq coords (list 
(list 2880.5625 -168.894) 
(list 2954.585 -169.044) 
(list 2954.585 -168.867) 
(list 2880.5625 -168.817)))
(apply 'command (append '("pline") coords '("c")))
(setq currobj (ssadd (entlast) currobj))
(setq coords (list 
(list 2880.5625 -168.674) 
(list 2954.585 -168.724) 
(list 2954.585 -168.547) 
(list 2880.5625 -168.597)))
(apply 'command (append '("pline") coords '("c")))
(setq currobj (ssadd (entlast) currobj))
(setq coords (list 
(list 2880.5625 -168.454) 
(list 2954.585 -168.404) 
(list 2954.585 -168.227) 
(list 2880.5625 -168.377)))
(apply 'command (append '("pline") coords '("c")))
(setq currobj (ssadd (entlast) currobj))
(setq coords (list 
(list 2880.5625 -168.234) 
(list 2954.585 -168.084) 
(list 2954.585 -167.907) 
(list 2880.5625 -168.157)))
(apply 'command (append '("pline") coords '("c")))
(setq currobj (ssadd (entlast) currobj))
(setq coords (list 
(list 2880.5625 -168.014) 
(list 2954.585 -167.764) 
(list 2954.585 -167.587) 
(list 2880.5625 -167.937)))
(apply 'command (append '("pline") coords '("c")))
(setq currobj (ssadd (entlast) currobj))
(setq coords (list 
(list 2880.5625 -167.794) 
(list 2954.585 -167.444) 
(list 2954.585 -167.267) 
(list 2880.5625 -167.717)))
(apply 'command (append '("pline") coords '("c")))
(setq currobj (ssadd (entlast) currobj))
(setq coords (list 
(list 2880.5625 -167.574) 
(list 2954.585 -167.124) 
(list 2954.585 -166.947) 
(list 2880.5625 -167.497)))
(apply 'command (append '("pline") coords '("c")))
(setq currobj (ssadd (entlast) currobj))
(setq coords (list 
(list 2880.5625 -167.354) 
(list 2954.585 -166.804) 
(list 2954.585 -166.627) 
(list 2880.5625 -167.277)))
(apply 'command (append '("pline") coords '("c")))
(setq currobj (ssadd (entlast) currobj))
(setq coords (list 
(list 2880.5625 -167.134) 
(list 2954.585 -166.484) 
(list 2954.585 -166.307) 
(list 2880.5625 -167.057)))
(apply 'command (append '("pline") coords '("c")))
(setq currobj (ssadd (entlast) currobj))
(setq coords (list 
(list 2879.4375 -167.057) 
(list 2805.415 -166.307) 
(list 2805.415 -166.484) 
(list 2879.4375 -167.134)))
(apply 'command (append '("pline") coords '("c")))
(setq currobj (ssadd (entlast) currobj))
(setq coords (list 
(list 2879.4375 -167.277) 
(list 2805.415 -166.627) 
(list 2805.415 -166.804) 
(list 2879.4375 -167.354)))
(apply 'command (append '("pline") coords '("c")))
(setq currobj (ssadd (entlast) currobj))
(setq coords (list 
(list 2879.4375 -167.497) 
(list 2805.415 -166.947) 
(list 2805.415 -167.124) 
(list 2879.4375 -167.574)))
(apply 'command (append '("pline") coords '("c")))
(setq currobj (ssadd (entlast) currobj))
(setq coords (list 
(list 2879.4375 -167.717) 
(list 2805.415 -167.267) 
(list 2805.415 -167.444) 
(list 2879.4375 -167.794)))
(apply 'command (append '("pline") coords '("c")))
(setq currobj (ssadd (entlast) currobj))
(setq coords (list 
(list 2879.4375 -167.937) 
(list 2805.415 -167.587) 
(list 2805.415 -167.764) 
(list 2879.4375 -168.014)))
(apply 'command (append '("pline") coords '("c")))
(setq currobj (ssadd (entlast) currobj))
(setq coords (list 
(list 2879.4375 -168.157) 
(list 2805.415 -167.907) 
(list 2805.415 -168.084) 
(list 2879.4375 -168.234)))
(apply 'command (append '("pline") coords '("c")))
(setq currobj (ssadd (entlast) currobj))
(setq coords (list 
(list 2879.4375 -168.377) 
(list 2805.415 -168.227) 
(list 2805.415 -168.404) 
(list 2879.4375 -168.454)))
(apply 'command (append '("pline") coords '("c")))
(setq currobj (ssadd (entlast) currobj))
(setq coords (list 
(list 2879.4375 -168.597) 
(list 2805.415 -168.547) 
(list 2805.415 -168.724) 
(list 2879.4375 -168.674)))
(apply 'command (append '("pline") coords '("c")))
(setq currobj (ssadd (entlast) currobj))
(setq coords (list 
(list 2879.4375 -168.817) 
(list 2805.415 -168.867) 
(list 2805.415 -169.044) 
(list 2879.4375 -168.894)))
(apply 'command (append '("pline") coords '("c")))
(setq currobj (ssadd (entlast) currobj))
(setq coords (list 
(list 2879.4375 -169.037) 
(list 2805.415 -169.187) 
(list 2805.415 -169.364) 
(list 2879.4375 -169.114)))
(apply 'command (append '("pline") coords '("c")))
(setq currobj (ssadd (entlast) currobj))
(setq coords (list 
(list 2879.4375 -169.257) 
(list 2805.415 -169.507) 
(list 2805.415 -169.684) 
(list 2879.4375 -169.334)))
(apply 'command (append '("pline") coords '("c")))
(setq currobj (ssadd (entlast) currobj))
(setq coords (list 
(list 2879.4375 -169.477) 
(list 2805.415 -169.827) 
(list 2805.415 -170.004) 
(list 2879.4375 -169.554)))
(apply 'command (append '("pline") coords '("c")))
(setq currobj (ssadd (entlast) currobj))
(setq coords (list 
(list 2879.4375 -169.697) 
(list 2805.415 -170.147) 
(list 2805.415 -170.324) 
(list 2879.4375 -169.774)))
(apply 'command (append '("pline") coords '("c")))
(setq currobj (ssadd (entlast) currobj))
(setq coords (list 
(list 2879.4375 -169.917) 
(list 2805.415 -170.467) 
(list 2805.415 -170.644) 
(list 2879.4375 -169.994)))
(apply 'command (append '("pline") coords '("c")))
(setq currobj (ssadd (entlast) currobj))
(setq coords (list 
(list 2879.4375 -170.137) 
(list 2805.415 -170.787) 
(list 2805.415 -170.964) 
(list 2879.4375 -170.214)))
(apply 'command (append '("pline") coords '("c")))
(setq currobj (ssadd (entlast) currobj))
(command "_layer" "set" "nitride" "")
(command "_layer" "set" "text" "")
(command "_circle" "2879.0625,-181.357" "0.075")
(command "_circle" "2879.0625,-181.057" "0.075")
(command "_circle" "2879.0625,-180.757" "0.075")
(command "_circle" "2879.0625,-180.457" "0.075")
(command "_circle" "2879.0625,-180.157" "0.075")
(command "_circle" "2878.7625,-181.357" "0.075")
(command "_circle" "2878.7625,-181.057" "0.075")
(command "_circle" "2878.7625,-180.757" "0.075")
(command "_circle" "2878.7625,-180.457" "0.075")
(command "_circle" "2878.7625,-180.157" "0.075")
(command "_circle" "2878.4625,-181.357" "0.075")
(command "_circle" "2878.4625,-181.057" "0.075")
(command "_circle" "2878.4625,-180.757" "0.075")
(command "_circle" "2878.4625,-180.457" "0.075")
(command "_circle" "2878.4625,-180.157" "0.075")
(command "_circle" "2878.1625,-181.357" "0.075")
(command "_circle" "2878.1625,-181.057" "0.075")
(command "_circle" "2878.1625,-180.757" "0.075")
(command "_circle" "2878.1625,-180.457" "0.075")
(command "_circle" "2878.1625,-180.157" "0.075")
(command "_circle" "2877.8625,-181.357" "0.075")
(command "_circle" "2877.8625,-181.057" "0.075")
(command "_circle" "2877.8625,-180.757" "0.075")
(command "_circle" "2877.8625,-180.457" "0.075")
(command "_circle" "2877.8625,-180.157" "0.075")
(command "_layer" "set" "nitride" "")
(setq coords (list 
(list 2880.2625 -155.914) 
(list 2880.2625 -40.2693) 
(list 2879.7375 -40.2693) 
(list 2879.7375 -155.914)))
(apply 'command (append '("pline") coords '("c")))
(setq currobj (ssadd (entlast) currobj))
(command "_layer" "set" "prebias" "")
(command "_rectangle" "2879.7375,-155.914" "2880.2625,-40.2693")
(setq currobj (ssadd (entlast) currobj))
(command "_layer" "set" "nitride" "")
(setq coords (list 
(list 2880.2625 -40.2693) 
(list 2880.5625 -30.2693) 
(list 2880.5625 -30.2693) 
(list 2880.5625 -29.2693) 
(list 2954.585 -30.0193) 
(list 2954.585 -25.0763) 
(list 2880.5625 -25.8263) 
(list 2880.5625 -24.8263) 
(list 2880.5625 -24.8263) 
(list 2880.2625 -14.8263) 
(list 2879.7375 -14.8263) 
(list 2879.4375 -24.8263) 
(list 2879.4375 -24.8263) 
(list 2879.4375 -25.8263) 
(list 2805.415 -25.0763) 
(list 2805.415 -30.0193) 
(list 2879.4375 -29.2693) 
(list 2879.4375 -30.2693) 
(list 2879.4375 -30.2693) 
(list 2879.7375 -40.2693)))
(apply 'command (append '("pline") coords '("c")))
(setq currobj (ssadd (entlast) currobj))
(command "_layer" "set" "prebias" "")
(setq coords (list 
(list 2879.4375 -40.2693) 
(list 2879.4375 -29.2693) 
(list 2805.415 -30.0193) 
(list 2805.415 -25.0763) 
(list 2879.4375 -25.8263) 
(list 2879.4375 -14.8263) 
(list 2880.5625 -14.8263) 
(list 2880.5625 -25.8263) 
(list 2954.585 -25.0763) 
(list 2954.585 -30.0193) 
(list 2880.5625 -29.2693) 
(list 2880.5625 -40.2693)))
(apply 'command (append '("pline") coords '("c")))
(setq currobj (ssadd (entlast) currobj))
(command "_layer" "set" "nitride" "")
(command "_layer" "set" "fda1" "")
(setq coords (list 
(list 2880.5625 -29.1263) 
(list 2954.585 -29.8763) 
(list 2954.585 -29.6993) 
(list 2880.5625 -29.0493)))
(apply 'command (append '("pline") coords '("c")))
(setq currobj (ssadd (entlast) currobj))
(setq coords (list 
(list 2880.5625 -28.9063) 
(list 2954.585 -29.5563) 
(list 2954.585 -29.3793) 
(list 2880.5625 -28.8293)))
(apply 'command (append '("pline") coords '("c")))
(setq currobj (ssadd (entlast) currobj))
(setq coords (list 
(list 2880.5625 -28.6863) 
(list 2954.585 -29.2363) 
(list 2954.585 -29.0593) 
(list 2880.5625 -28.6093)))
(apply 'command (append '("pline") coords '("c")))
(setq currobj (ssadd (entlast) currobj))
(setq coords (list 
(list 2880.5625 -28.4663) 
(list 2954.585 -28.9163) 
(list 2954.585 -28.7393) 
(list 2880.5625 -28.3893)))
(apply 'command (append '("pline") coords '("c")))
(setq currobj (ssadd (entlast) currobj))
(setq coords (list 
(list 2880.5625 -28.2463) 
(list 2954.585 -28.5963) 
(list 2954.585 -28.4193) 
(list 2880.5625 -28.1693)))
(apply 'command (append '("pline") coords '("c")))
(setq currobj (ssadd (entlast) currobj))
(setq coords (list 
(list 2880.5625 -28.0263) 
(list 2954.585 -28.2763) 
(list 2954.585 -28.0993) 
(list 2880.5625 -27.9493)))
(apply 'command (append '("pline") coords '("c")))
(setq currobj (ssadd (entlast) currobj))
(setq coords (list 
(list 2880.5625 -27.8063) 
(list 2954.585 -27.9563) 
(list 2954.585 -27.7793) 
(list 2880.5625 -27.7293)))
(apply 'command (append '("pline") coords '("c")))
(setq currobj (ssadd (entlast) currobj))
(setq coords (list 
(list 2880.5625 -27.5863) 
(list 2954.585 -27.6363) 
(list 2954.585 -27.4593) 
(list 2880.5625 -27.5093)))
(apply 'command (append '("pline") coords '("c")))
(setq currobj (ssadd (entlast) currobj))
(setq coords (list 
(list 2880.5625 -27.3663) 
(list 2954.585 -27.3163) 
(list 2954.585 -27.1393) 
(list 2880.5625 -27.2893)))
(apply 'command (append '("pline") coords '("c")))
(setq currobj (ssadd (entlast) currobj))
(setq coords (list 
(list 2880.5625 -27.1463) 
(list 2954.585 -26.9963) 
(list 2954.585 -26.8193) 
(list 2880.5625 -27.0693)))
(apply 'command (append '("pline") coords '("c")))
(setq currobj (ssadd (entlast) currobj))
(setq coords (list 
(list 2880.5625 -26.9263) 
(list 2954.585 -26.6763) 
(list 2954.585 -26.4993) 
(list 2880.5625 -26.8493)))
(apply 'command (append '("pline") coords '("c")))
(setq currobj (ssadd (entlast) currobj))
(setq coords (list 
(list 2880.5625 -26.7063) 
(list 2954.585 -26.3563) 
(list 2954.585 -26.1793) 
(list 2880.5625 -26.6293)))
(apply 'command (append '("pline") coords '("c")))
(setq currobj (ssadd (entlast) currobj))
(setq coords (list 
(list 2880.5625 -26.4863) 
(list 2954.585 -26.0363) 
(list 2954.585 -25.8593) 
(list 2880.5625 -26.4093)))
(apply 'command (append '("pline") coords '("c")))
(setq currobj (ssadd (entlast) currobj))
(setq coords (list 
(list 2880.5625 -26.2663) 
(list 2954.585 -25.7163) 
(list 2954.585 -25.5393) 
(list 2880.5625 -26.1893)))
(apply 'command (append '("pline") coords '("c")))
(setq currobj (ssadd (entlast) currobj))
(setq coords (list 
(list 2880.5625 -26.0463) 
(list 2954.585 -25.3963) 
(list 2954.585 -25.2193) 
(list 2880.5625 -25.9693)))
(apply 'command (append '("pline") coords '("c")))
(setq currobj (ssadd (entlast) currobj))
(setq coords (list 
(list 2879.4375 -25.9693) 
(list 2805.415 -25.2193) 
(list 2805.415 -25.3963) 
(list 2879.4375 -26.0463)))
(apply 'command (append '("pline") coords '("c")))
(setq currobj (ssadd (entlast) currobj))
(setq coords (list 
(list 2879.4375 -26.1893) 
(list 2805.415 -25.5393) 
(list 2805.415 -25.7163) 
(list 2879.4375 -26.2663)))
(apply 'command (append '("pline") coords '("c")))
(setq currobj (ssadd (entlast) currobj))
(setq coords (list 
(list 2879.4375 -26.4093) 
(list 2805.415 -25.8593) 
(list 2805.415 -26.0363) 
(list 2879.4375 -26.4863)))
(apply 'command (append '("pline") coords '("c")))
(setq currobj (ssadd (entlast) currobj))
(setq coords (list 
(list 2879.4375 -26.6293) 
(list 2805.415 -26.1793) 
(list 2805.415 -26.3563) 
(list 2879.4375 -26.7063)))
(apply 'command (append '("pline") coords '("c")))
(setq currobj (ssadd (entlast) currobj))
(setq coords (list 
(list 2879.4375 -26.8493) 
(list 2805.415 -26.4993) 
(list 2805.415 -26.6763) 
(list 2879.4375 -26.9263)))
(apply 'command (append '("pline") coords '("c")))
(setq currobj (ssadd (entlast) currobj))
(setq coords (list 
(list 2879.4375 -27.0693) 
(list 2805.415 -26.8193) 
(list 2805.415 -26.9963) 
(list 2879.4375 -27.1463)))
(apply 'command (append '("pline") coords '("c")))
(setq currobj (ssadd (entlast) currobj))
(setq coords (list 
(list 2879.4375 -27.2893) 
(list 2805.415 -27.1393) 
(list 2805.415 -27.3163) 
(list 2879.4375 -27.3663)))
(apply 'command (append '("pline") coords '("c")))
(setq currobj (ssadd (entlast) currobj))
(setq coords (list 
(list 2879.4375 -27.5093) 
(list 2805.415 -27.4593) 
(list 2805.415 -27.6363) 
(list 2879.4375 -27.5863)))
(apply 'command (append '("pline") coords '("c")))
(setq currobj (ssadd (entlast) currobj))
(setq coords (list 
(list 2879.4375 -27.7293) 
(list 2805.415 -27.7793) 
(list 2805.415 -27.9563) 
(list 2879.4375 -27.8063)))
(apply 'command (append '("pline") coords '("c")))
(setq currobj (ssadd (entlast) currobj))
(setq coords (list 
(list 2879.4375 -27.9493) 
(list 2805.415 -28.0993) 
(list 2805.415 -28.2763) 
(list 2879.4375 -28.0263)))
(apply 'command (append '("pline") coords '("c")))
(setq currobj (ssadd (entlast) currobj))
(setq coords (list 
(list 2879.4375 -28.1693) 
(list 2805.415 -28.4193) 
(list 2805.415 -28.5963) 
(list 2879.4375 -28.2463)))
(apply 'command (append '("pline") coords '("c")))
(setq currobj (ssadd (entlast) currobj))
(setq coords (list 
(list 2879.4375 -28.3893) 
(list 2805.415 -28.7393) 
(list 2805.415 -28.9163) 
(list 2879.4375 -28.4663)))
(apply 'command (append '("pline") coords '("c")))
(setq currobj (ssadd (entlast) currobj))
(setq coords (list 
(list 2879.4375 -28.6093) 
(list 2805.415 -29.0593) 
(list 2805.415 -29.2363) 
(list 2879.4375 -28.6863)))
(apply 'command (append '("pline") coords '("c")))
(setq currobj (ssadd (entlast) currobj))
(setq coords (list 
(list 2879.4375 -28.8293) 
(list 2805.415 -29.3793) 
(list 2805.415 -29.5563) 
(list 2879.4375 -28.9063)))
(apply 'command (append '("pline") coords '("c")))
(setq currobj (ssadd (entlast) currobj))
(setq coords (list 
(list 2879.4375 -29.0493) 
(list 2805.415 -29.6993) 
(list 2805.415 -29.8763) 
(list 2879.4375 -29.1263)))
(apply 'command (append '("pline") coords '("c")))
(setq currobj (ssadd (entlast) currobj))
(command "_layer" "set" "nitride" "")
(command "_layer" "set" "text" "")
(command "_circle" "2879.0625,-40.2693" "0.075")
(command "_circle" "2879.0625,-39.9693" "0.075")
(command "_circle" "2879.0625,-39.6693" "0.075")
(command "_circle" "2879.0625,-39.3693" "0.075")
(command "_circle" "2879.0625,-39.0693" "0.075")
(command "_circle" "2878.7625,-40.2693" "0.075")
(command "_circle" "2878.7625,-39.9693" "0.075")
(command "_circle" "2878.7625,-39.6693" "0.075")
(command "_circle" "2878.7625,-39.3693" "0.075")
(command "_circle" "2878.7625,-39.0693" "0.075")
(command "_circle" "2878.4625,-40.2693" "0.075")
(command "_circle" "2878.4625,-39.9693" "0.075")
(command "_circle" "2878.4625,-39.6693" "0.075")
(command "_circle" "2878.4625,-39.3693" "0.075")
(command "_circle" "2878.4625,-39.0693" "0.075")
(command "_circle" "2878.1625,-40.2693" "0.075")
(command "_circle" "2878.1625,-39.9693" "0.075")
(command "_circle" "2878.1625,-39.6693" "0.075")
(command "_circle" "2878.1625,-39.3693" "0.075")
(command "_circle" "2878.1625,-39.0693" "0.075")
(command "_circle" "2877.8625,-40.2693" "0.075")
(command "_circle" "2877.8625,-39.9693" "0.075")
(command "_circle" "2877.8625,-39.6693" "0.075")
(command "_circle" "2877.8625,-39.3693" "0.075")
(command "_circle" "2877.8625,-39.0693" "0.075")
(command "_layer" "set" "nitride" "")
(setq coords (list 
(list 2880.2625 -14.8263) 
(list 2880.2625 100.8184) 
(list 2879.7375 100.8184) 
(list 2879.7375 -14.8263)))
(apply 'command (append '("pline") coords '("c")))
(setq currobj (ssadd (entlast) currobj))
(command "_layer" "set" "prebias" "")
(command "_rectangle" "2879.7375,-14.8263" "2880.2625,100.8184")
(setq currobj (ssadd (entlast) currobj))
(command "_layer" "set" "nitride" "")
(setq coords (list 
(list 2880.2625 100.8184) 
(list 2880.5625 110.8184) 
(list 2880.5625 110.8184) 
(list 2880.5625 111.8184) 
(list 2954.585 111.0684) 
(list 2954.585 116.0114) 
(list 2880.5625 115.2614) 
(list 2880.5625 116.2614) 
(list 2880.5625 116.2614) 
(list 2880.2625 126.2614) 
(list 2879.7375 126.2614) 
(list 2879.4375 116.2614) 
(list 2879.4375 116.2614) 
(list 2879.4375 115.2614) 
(list 2805.415 116.0114) 
(list 2805.415 111.0684) 
(list 2879.4375 111.8184) 
(list 2879.4375 110.8184) 
(list 2879.4375 110.8184) 
(list 2879.7375 100.8184)))
(apply 'command (append '("pline") coords '("c")))
(setq currobj (ssadd (entlast) currobj))
(command "_layer" "set" "prebias" "")
(setq coords (list 
(list 2879.4375 100.8184) 
(list 2879.4375 111.8184) 
(list 2805.415 111.0684) 
(list 2805.415 116.0114) 
(list 2879.4375 115.2614) 
(list 2879.4375 126.2614) 
(list 2880.5625 126.2614) 
(list 2880.5625 115.2614) 
(list 2954.585 116.0114) 
(list 2954.585 111.0684) 
(list 2880.5625 111.8184) 
(list 2880.5625 100.8184)))
(apply 'command (append '("pline") coords '("c")))
(setq currobj (ssadd (entlast) currobj))
(command "_layer" "set" "nitride" "")
(command "_layer" "set" "fda1" "")
(setq coords (list 
(list 2880.5625 111.9614) 
(list 2954.585 111.2114) 
(list 2954.585 111.3884) 
(list 2880.5625 112.0384)))
(apply 'command (append '("pline") coords '("c")))
(setq currobj (ssadd (entlast) currobj))
(setq coords (list 
(list 2880.5625 112.1814) 
(list 2954.585 111.5314) 
(list 2954.585 111.7084) 
(list 2880.5625 112.2584)))
(apply 'command (append '("pline") coords '("c")))
(setq currobj (ssadd (entlast) currobj))
(setq coords (list 
(list 2880.5625 112.4014) 
(list 2954.585 111.8514) 
(list 2954.585 112.0284) 
(list 2880.5625 112.4784)))
(apply 'command (append '("pline") coords '("c")))
(setq currobj (ssadd (entlast) currobj))
(setq coords (list 
(list 2880.5625 112.6214) 
(list 2954.585 112.1714) 
(list 2954.585 112.3484) 
(list 2880.5625 112.6984)))
(apply 'command (append '("pline") coords '("c")))
(setq currobj (ssadd (entlast) currobj))
(setq coords (list 
(list 2880.5625 112.8414) 
(list 2954.585 112.4914) 
(list 2954.585 112.6684) 
(list 2880.5625 112.9184)))
(apply 'command (append '("pline") coords '("c")))
(setq currobj (ssadd (entlast) currobj))
(setq coords (list 
(list 2880.5625 113.0614) 
(list 2954.585 112.8114) 
(list 2954.585 112.9884) 
(list 2880.5625 113.1384)))
(apply 'command (append '("pline") coords '("c")))
(setq currobj (ssadd (entlast) currobj))
(setq coords (list 
(list 2880.5625 113.2814) 
(list 2954.585 113.1314) 
(list 2954.585 113.3084) 
(list 2880.5625 113.3584)))
(apply 'command (append '("pline") coords '("c")))
(setq currobj (ssadd (entlast) currobj))
(setq coords (list 
(list 2880.5625 113.5014) 
(list 2954.585 113.4514) 
(list 2954.585 113.6284) 
(list 2880.5625 113.5784)))
(apply 'command (append '("pline") coords '("c")))
(setq currobj (ssadd (entlast) currobj))
(setq coords (list 
(list 2880.5625 113.7214) 
(list 2954.585 113.7714) 
(list 2954.585 113.9484) 
(list 2880.5625 113.7984)))
(apply 'command (append '("pline") coords '("c")))
(setq currobj (ssadd (entlast) currobj))
(setq coords (list 
(list 2880.5625 113.9414) 
(list 2954.585 114.0914) 
(list 2954.585 114.2684) 
(list 2880.5625 114.0184)))
(apply 'command (append '("pline") coords '("c")))
(setq currobj (ssadd (entlast) currobj))
(setq coords (list 
(list 2880.5625 114.1614) 
(list 2954.585 114.4114) 
(list 2954.585 114.5884) 
(list 2880.5625 114.2384)))
(apply 'command (append '("pline") coords '("c")))
(setq currobj (ssadd (entlast) currobj))
(setq coords (list 
(list 2880.5625 114.3814) 
(list 2954.585 114.7314) 
(list 2954.585 114.9084) 
(list 2880.5625 114.4584)))
(apply 'command (append '("pline") coords '("c")))
(setq currobj (ssadd (entlast) currobj))
(setq coords (list 
(list 2880.5625 114.6014) 
(list 2954.585 115.0514) 
(list 2954.585 115.2284) 
(list 2880.5625 114.6784)))
(apply 'command (append '("pline") coords '("c")))
(setq currobj (ssadd (entlast) currobj))
(setq coords (list 
(list 2880.5625 114.8214) 
(list 2954.585 115.3714) 
(list 2954.585 115.5484) 
(list 2880.5625 114.8984)))
(apply 'command (append '("pline") coords '("c")))
(setq currobj (ssadd (entlast) currobj))
(setq coords (list 
(list 2880.5625 115.0414) 
(list 2954.585 115.6914) 
(list 2954.585 115.8684) 
(list 2880.5625 115.1184)))
(apply 'command (append '("pline") coords '("c")))
(setq currobj (ssadd (entlast) currobj))
(setq coords (list 
(list 2879.4375 115.1184) 
(list 2805.415 115.8684) 
(list 2805.415 115.6914) 
(list 2879.4375 115.0414)))
(apply 'command (append '("pline") coords '("c")))
(setq currobj (ssadd (entlast) currobj))
(setq coords (list 
(list 2879.4375 114.8984) 
(list 2805.415 115.5484) 
(list 2805.415 115.3714) 
(list 2879.4375 114.8214)))
(apply 'command (append '("pline") coords '("c")))
(setq currobj (ssadd (entlast) currobj))
(setq coords (list 
(list 2879.4375 114.6784) 
(list 2805.415 115.2284) 
(list 2805.415 115.0514) 
(list 2879.4375 114.6014)))
(apply 'command (append '("pline") coords '("c")))
(setq currobj (ssadd (entlast) currobj))
(setq coords (list 
(list 2879.4375 114.4584) 
(list 2805.415 114.9084) 
(list 2805.415 114.7314) 
(list 2879.4375 114.3814)))
(apply 'command (append '("pline") coords '("c")))
(setq currobj (ssadd (entlast) currobj))
(setq coords (list 
(list 2879.4375 114.2384) 
(list 2805.415 114.5884) 
(list 2805.415 114.4114) 
(list 2879.4375 114.1614)))
(apply 'command (append '("pline") coords '("c")))
(setq currobj (ssadd (entlast) currobj))
(setq coords (list 
(list 2879.4375 114.0184) 
(list 2805.415 114.2684) 
(list 2805.415 114.0914) 
(list 2879.4375 113.9414)))
(apply 'command (append '("pline") coords '("c")))
(setq currobj (ssadd (entlast) currobj))
(setq coords (list 
(list 2879.4375 113.7984) 
(list 2805.415 113.9484) 
(list 2805.415 113.7714) 
(list 2879.4375 113.7214)))
(apply 'command (append '("pline") coords '("c")))
(setq currobj (ssadd (entlast) currobj))
(setq coords (list 
(list 2879.4375 113.5784) 
(list 2805.415 113.6284) 
(list 2805.415 113.4514) 
(list 2879.4375 113.5014)))
(apply 'command (append '("pline") coords '("c")))
(setq currobj (ssadd (entlast) currobj))
(setq coords (list 
(list 2879.4375 113.3584) 
(list 2805.415 113.3084) 
(list 2805.415 113.1314) 
(list 2879.4375 113.2814)))
(apply 'command (append '("pline") coords '("c")))
(setq currobj (ssadd (entlast) currobj))
(setq coords (list 
(list 2879.4375 113.1384) 
(list 2805.415 112.9884) 
(list 2805.415 112.8114) 
(list 2879.4375 113.0614)))
(apply 'command (append '("pline") coords '("c")))
(setq currobj (ssadd (entlast) currobj))
(setq coords (list 
(list 2879.4375 112.9184) 
(list 2805.415 112.6684) 
(list 2805.415 112.4914) 
(list 2879.4375 112.8414)))
(apply 'command (append '("pline") coords '("c")))
(setq currobj (ssadd (entlast) currobj))
(setq coords (list 
(list 2879.4375 112.6984) 
(list 2805.415 112.3484) 
(list 2805.415 112.1714) 
(list 2879.4375 112.6214)))
(apply 'command (append '("pline") coords '("c")))
(setq currobj (ssadd (entlast) currobj))
(setq coords (list 
(list 2879.4375 112.4784) 
(list 2805.415 112.0284) 
(list 2805.415 111.8514) 
(list 2879.4375 112.4014)))
(apply 'command (append '("pline") coords '("c")))
(setq currobj (ssadd (entlast) currobj))
(setq coords (list 
(list 2879.4375 112.2584) 
(list 2805.415 111.7084) 
(list 2805.415 111.5314) 
(list 2879.4375 112.1814)))
(apply 'command (append '("pline") coords '("c")))
(setq currobj (ssadd (entlast) currobj))
(setq coords (list 
(list 2879.4375 112.0384) 
(list 2805.415 111.3884) 
(list 2805.415 111.2114) 
(list 2879.4375 111.9614)))
(apply 'command (append '("pline") coords '("c")))
(setq currobj (ssadd (entlast) currobj))
(command "_layer" "set" "nitride" "")
(command "_layer" "set" "text" "")
(command "_circle" "2879.0625,100.8184" "0.075")
(command "_circle" "2879.0625,101.1184" "0.075")
(command "_circle" "2879.0625,101.4184" "0.075")
(command "_circle" "2879.0625,101.7184" "0.075")
(command "_circle" "2879.0625,102.0184" "0.075")
(command "_circle" "2878.7625,100.8184" "0.075")
(command "_circle" "2878.7625,101.1184" "0.075")
(command "_circle" "2878.7625,101.4184" "0.075")
(command "_circle" "2878.7625,101.7184" "0.075")
(command "_circle" "2878.7625,102.0184" "0.075")
(command "_circle" "2878.4625,100.8184" "0.075")
(command "_circle" "2878.4625,101.1184" "0.075")
(command "_circle" "2878.4625,101.4184" "0.075")
(command "_circle" "2878.4625,101.7184" "0.075")
(command "_circle" "2878.4625,102.0184" "0.075")
(command "_circle" "2878.1625,100.8184" "0.075")
(command "_circle" "2878.1625,101.1184" "0.075")
(command "_circle" "2878.1625,101.4184" "0.075")
(command "_circle" "2878.1625,101.7184" "0.075")
(command "_circle" "2878.1625,102.0184" "0.075")
(command "_circle" "2877.8625,100.8184" "0.075")
(command "_circle" "2877.8625,101.1184" "0.075")
(command "_circle" "2877.8625,101.4184" "0.075")
(command "_circle" "2877.8625,101.7184" "0.075")
(command "_circle" "2877.8625,102.0184" "0.075")
(command "_layer" "set" "nitride" "")
(setq coords (list 
(list 2880.2625 126.2614) 
(list 2880.2625 241.9061) 
(list 2879.7375 241.9061) 
(list 2879.7375 126.2614)))
(apply 'command (append '("pline") coords '("c")))
(setq currobj (ssadd (entlast) currobj))
(command "_layer" "set" "prebias" "")
(command "_rectangle" "2879.7375,126.2614" "2880.2625,241.9061")
(setq currobj (ssadd (entlast) currobj))
(command "_layer" "set" "nitride" "")
(setq coords (list 
(list 2880.2625 241.9061) 
(list 2880.5625 251.9061) 
(list 2880.5625 251.9061) 
(list 2880.5625 252.9061) 
(list 2954.585 252.1561) 
(list 2954.585 257.0991) 
(list 2880.5625 256.3491) 
(list 2880.5625 257.3491) 
(list 2880.5625 257.3491) 
(list 2880.2625 267.3491) 
(list 2879.7375 267.3491) 
(list 2879.4375 257.3491) 
(list 2879.4375 257.3491) 
(list 2879.4375 256.3491) 
(list 2805.415 257.0991) 
(list 2805.415 252.1561) 
(list 2879.4375 252.9061) 
(list 2879.4375 251.9061) 
(list 2879.4375 251.9061) 
(list 2879.7375 241.9061)))
(apply 'command (append '("pline") coords '("c")))
(setq currobj (ssadd (entlast) currobj))
(command "_layer" "set" "prebias" "")
(setq coords (list 
(list 2879.4375 241.9061) 
(list 2879.4375 252.9061) 
(list 2805.415 252.1561) 
(list 2805.415 257.0991) 
(list 2879.4375 256.3491) 
(list 2879.4375 267.3491) 
(list 2880.5625 267.3491) 
(list 2880.5625 256.3491) 
(list 2954.585 257.0991) 
(list 2954.585 252.1561) 
(list 2880.5625 252.9061) 
(list 2880.5625 241.9061)))
(apply 'command (append '("pline") coords '("c")))
(setq currobj (ssadd (entlast) currobj))
(command "_layer" "set" "nitride" "")
(command "_layer" "set" "fda1" "")
(setq coords (list 
(list 2880.5625 253.0491) 
(list 2954.585 252.2991) 
(list 2954.585 252.4761) 
(list 2880.5625 253.1261)))
(apply 'command (append '("pline") coords '("c")))
(setq currobj (ssadd (entlast) currobj))
(setq coords (list 
(list 2880.5625 253.2691) 
(list 2954.585 252.6191) 
(list 2954.585 252.7961) 
(list 2880.5625 253.3461)))
(apply 'command (append '("pline") coords '("c")))
(setq currobj (ssadd (entlast) currobj))
(setq coords (list 
(list 2880.5625 253.4891) 
(list 2954.585 252.9391) 
(list 2954.585 253.1161) 
(list 2880.5625 253.5661)))
(apply 'command (append '("pline") coords '("c")))
(setq currobj (ssadd (entlast) currobj))
(setq coords (list 
(list 2880.5625 253.7091) 
(list 2954.585 253.2591) 
(list 2954.585 253.4361) 
(list 2880.5625 253.7861)))
(apply 'command (append '("pline") coords '("c")))
(setq currobj (ssadd (entlast) currobj))
(setq coords (list 
(list 2880.5625 253.9291) 
(list 2954.585 253.5791) 
(list 2954.585 253.7561) 
(list 2880.5625 254.0061)))
(apply 'command (append '("pline") coords '("c")))
(setq currobj (ssadd (entlast) currobj))
(setq coords (list 
(list 2880.5625 254.1491) 
(list 2954.585 253.8991) 
(list 2954.585 254.0761) 
(list 2880.5625 254.2261)))
(apply 'command (append '("pline") coords '("c")))
(setq currobj (ssadd (entlast) currobj))
(setq coords (list 
(list 2880.5625 254.3691) 
(list 2954.585 254.2191) 
(list 2954.585 254.3961) 
(list 2880.5625 254.4461)))
(apply 'command (append '("pline") coords '("c")))
(setq currobj (ssadd (entlast) currobj))
(setq coords (list 
(list 2880.5625 254.5891) 
(list 2954.585 254.5391) 
(list 2954.585 254.7161) 
(list 2880.5625 254.6661)))
(apply 'command (append '("pline") coords '("c")))
(setq currobj (ssadd (entlast) currobj))
(setq coords (list 
(list 2880.5625 254.8091) 
(list 2954.585 254.8591) 
(list 2954.585 255.0361) 
(list 2880.5625 254.8861)))
(apply 'command (append '("pline") coords '("c")))
(setq currobj (ssadd (entlast) currobj))
(setq coords (list 
(list 2880.5625 255.0291) 
(list 2954.585 255.1791) 
(list 2954.585 255.3561) 
(list 2880.5625 255.1061)))
(apply 'command (append '("pline") coords '("c")))
(setq currobj (ssadd (entlast) currobj))
(setq coords (list 
(list 2880.5625 255.2491) 
(list 2954.585 255.4991) 
(list 2954.585 255.6761) 
(list 2880.5625 255.3261)))
(apply 'command (append '("pline") coords '("c")))
(setq currobj (ssadd (entlast) currobj))
(setq coords (list 
(list 2880.5625 255.4691) 
(list 2954.585 255.8191) 
(list 2954.585 255.9961) 
(list 2880.5625 255.5461)))
(apply 'command (append '("pline") coords '("c")))
(setq currobj (ssadd (entlast) currobj))
(setq coords (list 
(list 2880.5625 255.6891) 
(list 2954.585 256.1391) 
(list 2954.585 256.3161) 
(list 2880.5625 255.7661)))
(apply 'command (append '("pline") coords '("c")))
(setq currobj (ssadd (entlast) currobj))
(setq coords (list 
(list 2880.5625 255.9091) 
(list 2954.585 256.4591) 
(list 2954.585 256.6361) 
(list 2880.5625 255.9861)))
(apply 'command (append '("pline") coords '("c")))
(setq currobj (ssadd (entlast) currobj))
(setq coords (list 
(list 2880.5625 256.1291) 
(list 2954.585 256.7791) 
(list 2954.585 256.9561) 
(list 2880.5625 256.2061)))
(apply 'command (append '("pline") coords '("c")))
(setq currobj (ssadd (entlast) currobj))
(setq coords (list 
(list 2879.4375 256.2061) 
(list 2805.415 256.9561) 
(list 2805.415 256.7791) 
(list 2879.4375 256.1291)))
(apply 'command (append '("pline") coords '("c")))
(setq currobj (ssadd (entlast) currobj))
(setq coords (list 
(list 2879.4375 255.9861) 
(list 2805.415 256.6361) 
(list 2805.415 256.4591) 
(list 2879.4375 255.9091)))
(apply 'command (append '("pline") coords '("c")))
(setq currobj (ssadd (entlast) currobj))
(setq coords (list 
(list 2879.4375 255.7661) 
(list 2805.415 256.3161) 
(list 2805.415 256.1391) 
(list 2879.4375 255.6891)))
(apply 'command (append '("pline") coords '("c")))
(setq currobj (ssadd (entlast) currobj))
(setq coords (list 
(list 2879.4375 255.5461) 
(list 2805.415 255.9961) 
(list 2805.415 255.8191) 
(list 2879.4375 255.4691)))
(apply 'command (append '("pline") coords '("c")))
(setq currobj (ssadd (entlast) currobj))
(setq coords (list 
(list 2879.4375 255.3261) 
(list 2805.415 255.6761) 
(list 2805.415 255.4991) 
(list 2879.4375 255.2491)))
(apply 'command (append '("pline") coords '("c")))
(setq currobj (ssadd (entlast) currobj))
(setq coords (list 
(list 2879.4375 255.1061) 
(list 2805.415 255.3561) 
(list 2805.415 255.1791) 
(list 2879.4375 255.0291)))
(apply 'command (append '("pline") coords '("c")))
(setq currobj (ssadd (entlast) currobj))
(setq coords (list 
(list 2879.4375 254.8861) 
(list 2805.415 255.0361) 
(list 2805.415 254.8591) 
(list 2879.4375 254.8091)))
(apply 'command (append '("pline") coords '("c")))
(setq currobj (ssadd (entlast) currobj))
(setq coords (list 
(list 2879.4375 254.6661) 
(list 2805.415 254.7161) 
(list 2805.415 254.5391) 
(list 2879.4375 254.5891)))
(apply 'command (append '("pline") coords '("c")))
(setq currobj (ssadd (entlast) currobj))
(setq coords (list 
(list 2879.4375 254.4461) 
(list 2805.415 254.3961) 
(list 2805.415 254.2191) 
(list 2879.4375 254.3691)))
(apply 'command (append '("pline") coords '("c")))
(setq currobj (ssadd (entlast) currobj))
(setq coords (list 
(list 2879.4375 254.2261) 
(list 2805.415 254.0761) 
(list 2805.415 253.8991) 
(list 2879.4375 254.1491)))
(apply 'command (append '("pline") coords '("c")))
(setq currobj (ssadd (entlast) currobj))
(setq coords (list 
(list 2879.4375 254.0061) 
(list 2805.415 253.7561) 
(list 2805.415 253.5791) 
(list 2879.4375 253.9291)))
(apply 'command (append '("pline") coords '("c")))
(setq currobj (ssadd (entlast) currobj))
(setq coords (list 
(list 2879.4375 253.7861) 
(list 2805.415 253.4361) 
(list 2805.415 253.2591) 
(list 2879.4375 253.7091)))
(apply 'command (append '("pline") coords '("c")))
(setq currobj (ssadd (entlast) currobj))
(setq coords (list 
(list 2879.4375 253.5661) 
(list 2805.415 253.1161) 
(list 2805.415 252.9391) 
(list 2879.4375 253.4891)))
(apply 'command (append '("pline") coords '("c")))
(setq currobj (ssadd (entlast) currobj))
(setq coords (list 
(list 2879.4375 253.3461) 
(list 2805.415 252.7961) 
(list 2805.415 252.6191) 
(list 2879.4375 253.2691)))
(apply 'command (append '("pline") coords '("c")))
(setq currobj (ssadd (entlast) currobj))
(setq coords (list 
(list 2879.4375 253.1261) 
(list 2805.415 252.4761) 
(list 2805.415 252.2991) 
(list 2879.4375 253.0491)))
(apply 'command (append '("pline") coords '("c")))
(setq currobj (ssadd (entlast) currobj))
(command "_layer" "set" "nitride" "")
(command "_layer" "set" "text" "")
(command "_circle" "2879.0625,241.9061" "0.075")
(command "_circle" "2879.0625,242.2061" "0.075")
(command "_circle" "2879.0625,242.5061" "0.075")
(command "_circle" "2879.0625,242.8061" "0.075")
(command "_circle" "2879.0625,243.1061" "0.075")
(command "_circle" "2878.7625,241.9061" "0.075")
(command "_circle" "2878.7625,242.2061" "0.075")
(command "_circle" "2878.7625,242.5061" "0.075")
(command "_circle" "2878.7625,242.8061" "0.075")
(command "_circle" "2878.7625,243.1061" "0.075")
(command "_circle" "2878.4625,241.9061" "0.075")
(command "_circle" "2878.4625,242.2061" "0.075")
(command "_circle" "2878.4625,242.5061" "0.075")
(command "_circle" "2878.4625,242.8061" "0.075")
(command "_circle" "2878.4625,243.1061" "0.075")
(command "_circle" "2878.1625,241.9061" "0.075")
(command "_circle" "2878.1625,242.2061" "0.075")
(command "_circle" "2878.1625,242.5061" "0.075")
(command "_circle" "2878.1625,242.8061" "0.075")
(command "_circle" "2878.1625,243.1061" "0.075")
(command "_circle" "2877.8625,241.9061" "0.075")
(command "_circle" "2877.8625,242.2061" "0.075")
(command "_circle" "2877.8625,242.5061" "0.075")
(command "_circle" "2877.8625,242.8061" "0.075")
(command "_circle" "2877.8625,243.1061" "0.075")
(command "_layer" "set" "nitride" "")
(setq coords (list 
(list 2880.2625 267.3491) 
(list 2880.2625 382.9939) 
(list 2879.7375 382.9939) 
(list 2879.7375 267.3491)))
(apply 'command (append '("pline") coords '("c")))
(setq currobj (ssadd (entlast) currobj))
(command "_layer" "set" "prebias" "")
(command "_rectangle" "2879.7375,267.3491" "2880.2625,382.9939")
(setq currobj (ssadd (entlast) currobj))
(command "_layer" "set" "nitride" "")
(setq coords (list 
(list 2880.2625 382.9939) 
(list 2880.5625 392.9939) 
(list 2880.5625 392.9939) 
(list 2880.5625 393.9939) 
(list 2954.585 393.2439) 
(list 2954.585 398.1869) 
(list 2880.5625 397.4369) 
(list 2880.5625 398.4369) 
(list 2880.5625 398.4369) 
(list 2880.2625 408.4369) 
(list 2879.7375 408.4369) 
(list 2879.4375 398.4369) 
(list 2879.4375 398.4369) 
(list 2879.4375 397.4369) 
(list 2805.415 398.1869) 
(list 2805.415 393.2439) 
(list 2879.4375 393.9939) 
(list 2879.4375 392.9939) 
(list 2879.4375 392.9939) 
(list 2879.7375 382.9939)))
(apply 'command (append '("pline") coords '("c")))
(setq currobj (ssadd (entlast) currobj))
(command "_layer" "set" "prebias" "")
(setq coords (list 
(list 2879.4375 382.9939) 
(list 2879.4375 393.9939) 
(list 2805.415 393.2439) 
(list 2805.415 398.1869) 
(list 2879.4375 397.4369) 
(list 2879.4375 408.4369) 
(list 2880.5625 408.4369) 
(list 2880.5625 397.4369) 
(list 2954.585 398.1869) 
(list 2954.585 393.2439) 
(list 2880.5625 393.9939) 
(list 2880.5625 382.9939)))
(apply 'command (append '("pline") coords '("c")))
(setq currobj (ssadd (entlast) currobj))
(command "_layer" "set" "nitride" "")
(command "_layer" "set" "fda1" "")
(setq coords (list 
(list 2880.5625 394.1369) 
(list 2954.585 393.3869) 
(list 2954.585 393.5639) 
(list 2880.5625 394.2139)))
(apply 'command (append '("pline") coords '("c")))
(setq currobj (ssadd (entlast) currobj))
(setq coords (list 
(list 2880.5625 394.3569) 
(list 2954.585 393.7069) 
(list 2954.585 393.8839) 
(list 2880.5625 394.4339)))
(apply 'command (append '("pline") coords '("c")))
(setq currobj (ssadd (entlast) currobj))
(setq coords (list 
(list 2880.5625 394.5769) 
(list 2954.585 394.0269) 
(list 2954.585 394.2039) 
(list 2880.5625 394.6539)))
(apply 'command (append '("pline") coords '("c")))
(setq currobj (ssadd (entlast) currobj))
(setq coords (list 
(list 2880.5625 394.7969) 
(list 2954.585 394.3469) 
(list 2954.585 394.5239) 
(list 2880.5625 394.8739)))
(apply 'command (append '("pline") coords '("c")))
(setq currobj (ssadd (entlast) currobj))
(setq coords (list 
(list 2880.5625 395.0169) 
(list 2954.585 394.6669) 
(list 2954.585 394.8439) 
(list 2880.5625 395.0939)))
(apply 'command (append '("pline") coords '("c")))
(setq currobj (ssadd (entlast) currobj))
(setq coords (list 
(list 2880.5625 395.2369) 
(list 2954.585 394.9869) 
(list 2954.585 395.1639) 
(list 2880.5625 395.3139)))
(apply 'command (append '("pline") coords '("c")))
(setq currobj (ssadd (entlast) currobj))
(setq coords (list 
(list 2880.5625 395.4569) 
(list 2954.585 395.3069) 
(list 2954.585 395.4839) 
(list 2880.5625 395.5339)))
(apply 'command (append '("pline") coords '("c")))
(setq currobj (ssadd (entlast) currobj))
(setq coords (list 
(list 2880.5625 395.6769) 
(list 2954.585 395.6269) 
(list 2954.585 395.8039) 
(list 2880.5625 395.7539)))
(apply 'command (append '("pline") coords '("c")))
(setq currobj (ssadd (entlast) currobj))
(setq coords (list 
(list 2880.5625 395.8969) 
(list 2954.585 395.9469) 
(list 2954.585 396.1239) 
(list 2880.5625 395.9739)))
(apply 'command (append '("pline") coords '("c")))
(setq currobj (ssadd (entlast) currobj))
(setq coords (list 
(list 2880.5625 396.1169) 
(list 2954.585 396.2669) 
(list 2954.585 396.4439) 
(list 2880.5625 396.1939)))
(apply 'command (append '("pline") coords '("c")))
(setq currobj (ssadd (entlast) currobj))
(setq coords (list 
(list 2880.5625 396.3369) 
(list 2954.585 396.5869) 
(list 2954.585 396.7639) 
(list 2880.5625 396.4139)))
(apply 'command (append '("pline") coords '("c")))
(setq currobj (ssadd (entlast) currobj))
(setq coords (list 
(list 2880.5625 396.5569) 
(list 2954.585 396.9069) 
(list 2954.585 397.0839) 
(list 2880.5625 396.6339)))
(apply 'command (append '("pline") coords '("c")))
(setq currobj (ssadd (entlast) currobj))
(setq coords (list 
(list 2880.5625 396.7769) 
(list 2954.585 397.2269) 
(list 2954.585 397.4039) 
(list 2880.5625 396.8539)))
(apply 'command (append '("pline") coords '("c")))
(setq currobj (ssadd (entlast) currobj))
(setq coords (list 
(list 2880.5625 396.9969) 
(list 2954.585 397.5469) 
(list 2954.585 397.7239) 
(list 2880.5625 397.0739)))
(apply 'command (append '("pline") coords '("c")))
(setq currobj (ssadd (entlast) currobj))
(setq coords (list 
(list 2880.5625 397.2169) 
(list 2954.585 397.8669) 
(list 2954.585 398.0439) 
(list 2880.5625 397.2939)))
(apply 'command (append '("pline") coords '("c")))
(setq currobj (ssadd (entlast) currobj))
(setq coords (list 
(list 2879.4375 397.2939) 
(list 2805.415 398.0439) 
(list 2805.415 397.8669) 
(list 2879.4375 397.2169)))
(apply 'command (append '("pline") coords '("c")))
(setq currobj (ssadd (entlast) currobj))
(setq coords (list 
(list 2879.4375 397.0739) 
(list 2805.415 397.7239) 
(list 2805.415 397.5469) 
(list 2879.4375 396.9969)))
(apply 'command (append '("pline") coords '("c")))
(setq currobj (ssadd (entlast) currobj))
(setq coords (list 
(list 2879.4375 396.8539) 
(list 2805.415 397.4039) 
(list 2805.415 397.2269) 
(list 2879.4375 396.7769)))
(apply 'command (append '("pline") coords '("c")))
(setq currobj (ssadd (entlast) currobj))
(setq coords (list 
(list 2879.4375 396.6339) 
(list 2805.415 397.0839) 
(list 2805.415 396.9069) 
(list 2879.4375 396.5569)))
(apply 'command (append '("pline") coords '("c")))
(setq currobj (ssadd (entlast) currobj))
(setq coords (list 
(list 2879.4375 396.4139) 
(list 2805.415 396.7639) 
(list 2805.415 396.5869) 
(list 2879.4375 396.3369)))
(apply 'command (append '("pline") coords '("c")))
(setq currobj (ssadd (entlast) currobj))
(setq coords (list 
(list 2879.4375 396.1939) 
(list 2805.415 396.4439) 
(list 2805.415 396.2669) 
(list 2879.4375 396.1169)))
(apply 'command (append '("pline") coords '("c")))
(setq currobj (ssadd (entlast) currobj))
(setq coords (list 
(list 2879.4375 395.9739) 
(list 2805.415 396.1239) 
(list 2805.415 395.9469) 
(list 2879.4375 395.8969)))
(apply 'command (append '("pline") coords '("c")))
(setq currobj (ssadd (entlast) currobj))
(setq coords (list 
(list 2879.4375 395.7539) 
(list 2805.415 395.8039) 
(list 2805.415 395.6269) 
(list 2879.4375 395.6769)))
(apply 'command (append '("pline") coords '("c")))
(setq currobj (ssadd (entlast) currobj))
(setq coords (list 
(list 2879.4375 395.5339) 
(list 2805.415 395.4839) 
(list 2805.415 395.3069) 
(list 2879.4375 395.4569)))
(apply 'command (append '("pline") coords '("c")))
(setq currobj (ssadd (entlast) currobj))
(setq coords (list 
(list 2879.4375 395.3139) 
(list 2805.415 395.1639) 
(list 2805.415 394.9869) 
(list 2879.4375 395.2369)))
(apply 'command (append '("pline") coords '("c")))
(setq currobj (ssadd (entlast) currobj))
(setq coords (list 
(list 2879.4375 395.0939) 
(list 2805.415 394.8439) 
(list 2805.415 394.6669) 
(list 2879.4375 395.0169)))
(apply 'command (append '("pline") coords '("c")))
(setq currobj (ssadd (entlast) currobj))
(setq coords (list 
(list 2879.4375 394.8739) 
(list 2805.415 394.5239) 
(list 2805.415 394.3469) 
(list 2879.4375 394.7969)))
(apply 'command (append '("pline") coords '("c")))
(setq currobj (ssadd (entlast) currobj))
(setq coords (list 
(list 2879.4375 394.6539) 
(list 2805.415 394.2039) 
(list 2805.415 394.0269) 
(list 2879.4375 394.5769)))
(apply 'command (append '("pline") coords '("c")))
(setq currobj (ssadd (entlast) currobj))
(setq coords (list 
(list 2879.4375 394.4339) 
(list 2805.415 393.8839) 
(list 2805.415 393.7069) 
(list 2879.4375 394.3569)))
(apply 'command (append '("pline") coords '("c")))
(setq currobj (ssadd (entlast) currobj))
(setq coords (list 
(list 2879.4375 394.2139) 
(list 2805.415 393.5639) 
(list 2805.415 393.3869) 
(list 2879.4375 394.1369)))
(apply 'command (append '("pline") coords '("c")))
(setq currobj (ssadd (entlast) currobj))
(command "_layer" "set" "nitride" "")
(command "_layer" "set" "text" "")
(command "_circle" "2879.0625,382.9939" "0.075")
(command "_circle" "2879.0625,383.2939" "0.075")
(command "_circle" "2879.0625,383.5939" "0.075")
(command "_circle" "2879.0625,383.8939" "0.075")
(command "_circle" "2879.0625,384.1939" "0.075")
(command "_circle" "2878.7625,382.9939" "0.075")
(command "_circle" "2878.7625,383.2939" "0.075")
(command "_circle" "2878.7625,383.5939" "0.075")
(command "_circle" "2878.7625,383.8939" "0.075")
(command "_circle" "2878.7625,384.1939" "0.075")
(command "_circle" "2878.4625,382.9939" "0.075")
(command "_circle" "2878.4625,383.2939" "0.075")
(command "_circle" "2878.4625,383.5939" "0.075")
(command "_circle" "2878.4625,383.8939" "0.075")
(command "_circle" "2878.4625,384.1939" "0.075")
(command "_circle" "2878.1625,382.9939" "0.075")
(command "_circle" "2878.1625,383.2939" "0.075")
(command "_circle" "2878.1625,383.5939" "0.075")
(command "_circle" "2878.1625,383.8939" "0.075")
(command "_circle" "2878.1625,384.1939" "0.075")
(command "_circle" "2877.8625,382.9939" "0.075")
(command "_circle" "2877.8625,383.2939" "0.075")
(command "_circle" "2877.8625,383.5939" "0.075")
(command "_circle" "2877.8625,383.8939" "0.075")
(command "_circle" "2877.8625,384.1939" "0.075")
(command "_layer" "set" "nitride" "")
(setq coords (list 
(list 2880.2625 408.4369) 
(list 2880.2625 524.0816) 
(list 2879.7375 524.0816) 
(list 2879.7375 408.4369)))
(apply 'command (append '("pline") coords '("c")))
(setq currobj (ssadd (entlast) currobj))
(command "_layer" "set" "prebias" "")
(command "_rectangle" "2879.7375,408.4369" "2880.2625,524.0816")
(setq currobj (ssadd (entlast) currobj))
(command "_layer" "set" "nitride" "")
(setq coords (list 
(list 2880.2625 524.0816) 
(list 2880.5625 534.0816) 
(list 2880.5625 534.0816) 
(list 2880.5625 535.0816) 
(list 2954.585 534.3316) 
(list 2954.585 539.2746) 
(list 2880.5625 538.5246) 
(list 2880.5625 539.5246) 
(list 2880.5625 539.5246) 
(list 2880.2625 549.5246) 
(list 2879.7375 549.5246) 
(list 2879.4375 539.5246) 
(list 2879.4375 539.5246) 
(list 2879.4375 538.5246) 
(list 2805.415 539.2746) 
(list 2805.415 534.3316) 
(list 2879.4375 535.0816) 
(list 2879.4375 534.0816) 
(list 2879.4375 534.0816) 
(list 2879.7375 524.0816)))
(apply 'command (append '("pline") coords '("c")))
(setq currobj (ssadd (entlast) currobj))
(command "_layer" "set" "prebias" "")
(setq coords (list 
(list 2879.4375 524.0816) 
(list 2879.4375 535.0816) 
(list 2805.415 534.3316) 
(list 2805.415 539.2746) 
(list 2879.4375 538.5246) 
(list 2879.4375 549.5246) 
(list 2880.5625 549.5246) 
(list 2880.5625 538.5246) 
(list 2954.585 539.2746) 
(list 2954.585 534.3316) 
(list 2880.5625 535.0816) 
(list 2880.5625 524.0816)))
(apply 'command (append '("pline") coords '("c")))
(setq currobj (ssadd (entlast) currobj))
(command "_layer" "set" "nitride" "")
(command "_layer" "set" "fda1" "")
(setq coords (list 
(list 2880.5625 535.2246) 
(list 2954.585 534.4746) 
(list 2954.585 534.6516) 
(list 2880.5625 535.3016)))
(apply 'command (append '("pline") coords '("c")))
(setq currobj (ssadd (entlast) currobj))
(setq coords (list 
(list 2880.5625 535.4446) 
(list 2954.585 534.7946) 
(list 2954.585 534.9716) 
(list 2880.5625 535.5216)))
(apply 'command (append '("pline") coords '("c")))
(setq currobj (ssadd (entlast) currobj))
(setq coords (list 
(list 2880.5625 535.6646) 
(list 2954.585 535.1146) 
(list 2954.585 535.2916) 
(list 2880.5625 535.7416)))
(apply 'command (append '("pline") coords '("c")))
(setq currobj (ssadd (entlast) currobj))
(setq coords (list 
(list 2880.5625 535.8846) 
(list 2954.585 535.4346) 
(list 2954.585 535.6116) 
(list 2880.5625 535.9616)))
(apply 'command (append '("pline") coords '("c")))
(setq currobj (ssadd (entlast) currobj))
(setq coords (list 
(list 2880.5625 536.1046) 
(list 2954.585 535.7546) 
(list 2954.585 535.9316) 
(list 2880.5625 536.1816)))
(apply 'command (append '("pline") coords '("c")))
(setq currobj (ssadd (entlast) currobj))
(setq coords (list 
(list 2880.5625 536.3246) 
(list 2954.585 536.0746) 
(list 2954.585 536.2516) 
(list 2880.5625 536.4016)))
(apply 'command (append '("pline") coords '("c")))
(setq currobj (ssadd (entlast) currobj))
(setq coords (list 
(list 2880.5625 536.5446) 
(list 2954.585 536.3946) 
(list 2954.585 536.5716) 
(list 2880.5625 536.6216)))
(apply 'command (append '("pline") coords '("c")))
(setq currobj (ssadd (entlast) currobj))
(setq coords (list 
(list 2880.5625 536.7646) 
(list 2954.585 536.7146) 
(list 2954.585 536.8916) 
(list 2880.5625 536.8416)))
(apply 'command (append '("pline") coords '("c")))
(setq currobj (ssadd (entlast) currobj))
(setq coords (list 
(list 2880.5625 536.9846) 
(list 2954.585 537.0346) 
(list 2954.585 537.2116) 
(list 2880.5625 537.0616)))
(apply 'command (append '("pline") coords '("c")))
(setq currobj (ssadd (entlast) currobj))
(setq coords (list 
(list 2880.5625 537.2046) 
(list 2954.585 537.3546) 
(list 2954.585 537.5316) 
(list 2880.5625 537.2816)))
(apply 'command (append '("pline") coords '("c")))
(setq currobj (ssadd (entlast) currobj))
(setq coords (list 
(list 2880.5625 537.4246) 
(list 2954.585 537.6746) 
(list 2954.585 537.8516) 
(list 2880.5625 537.5016)))
(apply 'command (append '("pline") coords '("c")))
(setq currobj (ssadd (entlast) currobj))
(setq coords (list 
(list 2880.5625 537.6446) 
(list 2954.585 537.9946) 
(list 2954.585 538.1716) 
(list 2880.5625 537.7216)))
(apply 'command (append '("pline") coords '("c")))
(setq currobj (ssadd (entlast) currobj))
(setq coords (list 
(list 2880.5625 537.8646) 
(list 2954.585 538.3146) 
(list 2954.585 538.4916) 
(list 2880.5625 537.9416)))
(apply 'command (append '("pline") coords '("c")))
(setq currobj (ssadd (entlast) currobj))
(setq coords (list 
(list 2880.5625 538.0846) 
(list 2954.585 538.6346) 
(list 2954.585 538.8116) 
(list 2880.5625 538.1616)))
(apply 'command (append '("pline") coords '("c")))
(setq currobj (ssadd (entlast) currobj))
(setq coords (list 
(list 2880.5625 538.3046) 
(list 2954.585 538.9546) 
(list 2954.585 539.1316) 
(list 2880.5625 538.3816)))
(apply 'command (append '("pline") coords '("c")))
(setq currobj (ssadd (entlast) currobj))
(setq coords (list 
(list 2879.4375 538.3816) 
(list 2805.415 539.1316) 
(list 2805.415 538.9546) 
(list 2879.4375 538.3046)))
(apply 'command (append '("pline") coords '("c")))
(setq currobj (ssadd (entlast) currobj))
(setq coords (list 
(list 2879.4375 538.1616) 
(list 2805.415 538.8116) 
(list 2805.415 538.6346) 
(list 2879.4375 538.0846)))
(apply 'command (append '("pline") coords '("c")))
(setq currobj (ssadd (entlast) currobj))
(setq coords (list 
(list 2879.4375 537.9416) 
(list 2805.415 538.4916) 
(list 2805.415 538.3146) 
(list 2879.4375 537.8646)))
(apply 'command (append '("pline") coords '("c")))
(setq currobj (ssadd (entlast) currobj))
(setq coords (list 
(list 2879.4375 537.7216) 
(list 2805.415 538.1716) 
(list 2805.415 537.9946) 
(list 2879.4375 537.6446)))
(apply 'command (append '("pline") coords '("c")))
(setq currobj (ssadd (entlast) currobj))
(setq coords (list 
(list 2879.4375 537.5016) 
(list 2805.415 537.8516) 
(list 2805.415 537.6746) 
(list 2879.4375 537.4246)))
(apply 'command (append '("pline") coords '("c")))
(setq currobj (ssadd (entlast) currobj))
(setq coords (list 
(list 2879.4375 537.2816) 
(list 2805.415 537.5316) 
(list 2805.415 537.3546) 
(list 2879.4375 537.2046)))
(apply 'command (append '("pline") coords '("c")))
(setq currobj (ssadd (entlast) currobj))
(setq coords (list 
(list 2879.4375 537.0616) 
(list 2805.415 537.2116) 
(list 2805.415 537.0346) 
(list 2879.4375 536.9846)))
(apply 'command (append '("pline") coords '("c")))
(setq currobj (ssadd (entlast) currobj))
(setq coords (list 
(list 2879.4375 536.8416) 
(list 2805.415 536.8916) 
(list 2805.415 536.7146) 
(list 2879.4375 536.7646)))
(apply 'command (append '("pline") coords '("c")))
(setq currobj (ssadd (entlast) currobj))
(setq coords (list 
(list 2879.4375 536.6216) 
(list 2805.415 536.5716) 
(list 2805.415 536.3946) 
(list 2879.4375 536.5446)))
(apply 'command (append '("pline") coords '("c")))
(setq currobj (ssadd (entlast) currobj))
(setq coords (list 
(list 2879.4375 536.4016) 
(list 2805.415 536.2516) 
(list 2805.415 536.0746) 
(list 2879.4375 536.3246)))
(apply 'command (append '("pline") coords '("c")))
(setq currobj (ssadd (entlast) currobj))
(setq coords (list 
(list 2879.4375 536.1816) 
(list 2805.415 535.9316) 
(list 2805.415 535.7546) 
(list 2879.4375 536.1046)))
(apply 'command (append '("pline") coords '("c")))
(setq currobj (ssadd (entlast) currobj))
(setq coords (list 
(list 2879.4375 535.9616) 
(list 2805.415 535.6116) 
(list 2805.415 535.4346) 
(list 2879.4375 535.8846)))
(apply 'command (append '("pline") coords '("c")))
(setq currobj (ssadd (entlast) currobj))
(setq coords (list 
(list 2879.4375 535.7416) 
(list 2805.415 535.2916) 
(list 2805.415 535.1146) 
(list 2879.4375 535.6646)))
(apply 'command (append '("pline") coords '("c")))
(setq currobj (ssadd (entlast) currobj))
(setq coords (list 
(list 2879.4375 535.5216) 
(list 2805.415 534.9716) 
(list 2805.415 534.7946) 
(list 2879.4375 535.4446)))
(apply 'command (append '("pline") coords '("c")))
(setq currobj (ssadd (entlast) currobj))
(setq coords (list 
(list 2879.4375 535.3016) 
(list 2805.415 534.6516) 
(list 2805.415 534.4746) 
(list 2879.4375 535.2246)))
(apply 'command (append '("pline") coords '("c")))
(setq currobj (ssadd (entlast) currobj))
(command "_layer" "set" "nitride" "")
(command "_layer" "set" "text" "")
(command "_circle" "2879.0625,524.0816" "0.075")
(command "_circle" "2879.0625,524.3816" "0.075")
(command "_circle" "2879.0625,524.6816" "0.075")
(command "_circle" "2879.0625,524.9816" "0.075")
(command "_circle" "2879.0625,525.2816" "0.075")
(command "_circle" "2878.7625,524.0816" "0.075")
(command "_circle" "2878.7625,524.3816" "0.075")
(command "_circle" "2878.7625,524.6816" "0.075")
(command "_circle" "2878.7625,524.9816" "0.075")
(command "_circle" "2878.7625,525.2816" "0.075")
(command "_circle" "2878.4625,524.0816" "0.075")
(command "_circle" "2878.4625,524.3816" "0.075")
(command "_circle" "2878.4625,524.6816" "0.075")
(command "_circle" "2878.4625,524.9816" "0.075")
(command "_circle" "2878.4625,525.2816" "0.075")
(command "_circle" "2878.1625,524.0816" "0.075")
(command "_circle" "2878.1625,524.3816" "0.075")
(command "_circle" "2878.1625,524.6816" "0.075")
(command "_circle" "2878.1625,524.9816" "0.075")
(command "_circle" "2878.1625,525.2816" "0.075")
(command "_circle" "2877.8625,524.0816" "0.075")
(command "_circle" "2877.8625,524.3816" "0.075")
(command "_circle" "2877.8625,524.6816" "0.075")
(command "_circle" "2877.8625,524.9816" "0.075")
(command "_circle" "2877.8625,525.2816" "0.075")
(command "_layer" "set" "nitride" "")
(setq coords (list 
(list 2880.2625 549.5246) 
(list 2880.2625 665.1693) 
(list 2879.7375 665.1693) 
(list 2879.7375 549.5246)))
(apply 'command (append '("pline") coords '("c")))
(setq currobj (ssadd (entlast) currobj))
(command "_layer" "set" "prebias" "")
(command "_rectangle" "2879.7375,549.5246" "2880.2625,665.1693")
(setq currobj (ssadd (entlast) currobj))
(command "_layer" "set" "nitride" "")
(setq coords (list 
(list 2880.2625 665.1693) 
(list 2880.5625 675.1693) 
(list 2880.5625 675.1693) 
(list 2880.5625 676.1693) 
(list 2954.585 675.4193) 
(list 2954.585 680.3623) 
(list 2880.5625 679.6123) 
(list 2880.5625 680.6123) 
(list 2880.5625 680.6123) 
(list 2880.2625 690.6123) 
(list 2879.7375 690.6123) 
(list 2879.4375 680.6123) 
(list 2879.4375 680.6123) 
(list 2879.4375 679.6123) 
(list 2805.415 680.3623) 
(list 2805.415 675.4193) 
(list 2879.4375 676.1693) 
(list 2879.4375 675.1693) 
(list 2879.4375 675.1693) 
(list 2879.7375 665.1693)))
(apply 'command (append '("pline") coords '("c")))
(setq currobj (ssadd (entlast) currobj))
(command "_layer" "set" "prebias" "")
(setq coords (list 
(list 2879.4375 665.1693) 
(list 2879.4375 676.1693) 
(list 2805.415 675.4193) 
(list 2805.415 680.3623) 
(list 2879.4375 679.6123) 
(list 2879.4375 690.6123) 
(list 2880.5625 690.6123) 
(list 2880.5625 679.6123) 
(list 2954.585 680.3623) 
(list 2954.585 675.4193) 
(list 2880.5625 676.1693) 
(list 2880.5625 665.1693)))
(apply 'command (append '("pline") coords '("c")))
(setq currobj (ssadd (entlast) currobj))
(command "_layer" "set" "nitride" "")
(command "_layer" "set" "fda1" "")
(setq coords (list 
(list 2880.5625 676.3123) 
(list 2954.585 675.5623) 
(list 2954.585 675.7393) 
(list 2880.5625 676.3893)))
(apply 'command (append '("pline") coords '("c")))
(setq currobj (ssadd (entlast) currobj))
(setq coords (list 
(list 2880.5625 676.5323) 
(list 2954.585 675.8823) 
(list 2954.585 676.0593) 
(list 2880.5625 676.6093)))
(apply 'command (append '("pline") coords '("c")))
(setq currobj (ssadd (entlast) currobj))
(setq coords (list 
(list 2880.5625 676.7523) 
(list 2954.585 676.2023) 
(list 2954.585 676.3793) 
(list 2880.5625 676.8293)))
(apply 'command (append '("pline") coords '("c")))
(setq currobj (ssadd (entlast) currobj))
(setq coords (list 
(list 2880.5625 676.9723) 
(list 2954.585 676.5223) 
(list 2954.585 676.6993) 
(list 2880.5625 677.0493)))
(apply 'command (append '("pline") coords '("c")))
(setq currobj (ssadd (entlast) currobj))
(setq coords (list 
(list 2880.5625 677.1923) 
(list 2954.585 676.8423) 
(list 2954.585 677.0193) 
(list 2880.5625 677.2693)))
(apply 'command (append '("pline") coords '("c")))
(setq currobj (ssadd (entlast) currobj))
(setq coords (list 
(list 2880.5625 677.4123) 
(list 2954.585 677.1623) 
(list 2954.585 677.3393) 
(list 2880.5625 677.4893)))
(apply 'command (append '("pline") coords '("c")))
(setq currobj (ssadd (entlast) currobj))
(setq coords (list 
(list 2880.5625 677.6323) 
(list 2954.585 677.4823) 
(list 2954.585 677.6593) 
(list 2880.5625 677.7093)))
(apply 'command (append '("pline") coords '("c")))
(setq currobj (ssadd (entlast) currobj))
(setq coords (list 
(list 2880.5625 677.8523) 
(list 2954.585 677.8023) 
(list 2954.585 677.9793) 
(list 2880.5625 677.9293)))
(apply 'command (append '("pline") coords '("c")))
(setq currobj (ssadd (entlast) currobj))
(setq coords (list 
(list 2880.5625 678.0723) 
(list 2954.585 678.1223) 
(list 2954.585 678.2993) 
(list 2880.5625 678.1493)))
(apply 'command (append '("pline") coords '("c")))
(setq currobj (ssadd (entlast) currobj))
(setq coords (list 
(list 2880.5625 678.2923) 
(list 2954.585 678.4423) 
(list 2954.585 678.6193) 
(list 2880.5625 678.3693)))
(apply 'command (append '("pline") coords '("c")))
(setq currobj (ssadd (entlast) currobj))
(setq coords (list 
(list 2880.5625 678.5123) 
(list 2954.585 678.7623) 
(list 2954.585 678.9393) 
(list 2880.5625 678.5893)))
(apply 'command (append '("pline") coords '("c")))
(setq currobj (ssadd (entlast) currobj))
(setq coords (list 
(list 2880.5625 678.7323) 
(list 2954.585 679.0823) 
(list 2954.585 679.2593) 
(list 2880.5625 678.8093)))
(apply 'command (append '("pline") coords '("c")))
(setq currobj (ssadd (entlast) currobj))
(setq coords (list 
(list 2880.5625 678.9523) 
(list 2954.585 679.4023) 
(list 2954.585 679.5793) 
(list 2880.5625 679.0293)))
(apply 'command (append '("pline") coords '("c")))
(setq currobj (ssadd (entlast) currobj))
(setq coords (list 
(list 2880.5625 679.1723) 
(list 2954.585 679.7223) 
(list 2954.585 679.8993) 
(list 2880.5625 679.2493)))
(apply 'command (append '("pline") coords '("c")))
(setq currobj (ssadd (entlast) currobj))
(setq coords (list 
(list 2880.5625 679.3923) 
(list 2954.585 680.0423) 
(list 2954.585 680.2193) 
(list 2880.5625 679.4693)))
(apply 'command (append '("pline") coords '("c")))
(setq currobj (ssadd (entlast) currobj))
(setq coords (list 
(list 2879.4375 679.4693) 
(list 2805.415 680.2193) 
(list 2805.415 680.0423) 
(list 2879.4375 679.3923)))
(apply 'command (append '("pline") coords '("c")))
(setq currobj (ssadd (entlast) currobj))
(setq coords (list 
(list 2879.4375 679.2493) 
(list 2805.415 679.8993) 
(list 2805.415 679.7223) 
(list 2879.4375 679.1723)))
(apply 'command (append '("pline") coords '("c")))
(setq currobj (ssadd (entlast) currobj))
(setq coords (list 
(list 2879.4375 679.0293) 
(list 2805.415 679.5793) 
(list 2805.415 679.4023) 
(list 2879.4375 678.9523)))
(apply 'command (append '("pline") coords '("c")))
(setq currobj (ssadd (entlast) currobj))
(setq coords (list 
(list 2879.4375 678.8093) 
(list 2805.415 679.2593) 
(list 2805.415 679.0823) 
(list 2879.4375 678.7323)))
(apply 'command (append '("pline") coords '("c")))
(setq currobj (ssadd (entlast) currobj))
(setq coords (list 
(list 2879.4375 678.5893) 
(list 2805.415 678.9393) 
(list 2805.415 678.7623) 
(list 2879.4375 678.5123)))
(apply 'command (append '("pline") coords '("c")))
(setq currobj (ssadd (entlast) currobj))
(setq coords (list 
(list 2879.4375 678.3693) 
(list 2805.415 678.6193) 
(list 2805.415 678.4423) 
(list 2879.4375 678.2923)))
(apply 'command (append '("pline") coords '("c")))
(setq currobj (ssadd (entlast) currobj))
(setq coords (list 
(list 2879.4375 678.1493) 
(list 2805.415 678.2993) 
(list 2805.415 678.1223) 
(list 2879.4375 678.0723)))
(apply 'command (append '("pline") coords '("c")))
(setq currobj (ssadd (entlast) currobj))
(setq coords (list 
(list 2879.4375 677.9293) 
(list 2805.415 677.9793) 
(list 2805.415 677.8023) 
(list 2879.4375 677.8523)))
(apply 'command (append '("pline") coords '("c")))
(setq currobj (ssadd (entlast) currobj))
(setq coords (list 
(list 2879.4375 677.7093) 
(list 2805.415 677.6593) 
(list 2805.415 677.4823) 
(list 2879.4375 677.6323)))
(apply 'command (append '("pline") coords '("c")))
(setq currobj (ssadd (entlast) currobj))
(setq coords (list 
(list 2879.4375 677.4893) 
(list 2805.415 677.3393) 
(list 2805.415 677.1623) 
(list 2879.4375 677.4123)))
(apply 'command (append '("pline") coords '("c")))
(setq currobj (ssadd (entlast) currobj))
(setq coords (list 
(list 2879.4375 677.2693) 
(list 2805.415 677.0193) 
(list 2805.415 676.8423) 
(list 2879.4375 677.1923)))
(apply 'command (append '("pline") coords '("c")))
(setq currobj (ssadd (entlast) currobj))
(setq coords (list 
(list 2879.4375 677.0493) 
(list 2805.415 676.6993) 
(list 2805.415 676.5223) 
(list 2879.4375 676.9723)))
(apply 'command (append '("pline") coords '("c")))
(setq currobj (ssadd (entlast) currobj))
(setq coords (list 
(list 2879.4375 676.8293) 
(list 2805.415 676.3793) 
(list 2805.415 676.2023) 
(list 2879.4375 676.7523)))
(apply 'command (append '("pline") coords '("c")))
(setq currobj (ssadd (entlast) currobj))
(setq coords (list 
(list 2879.4375 676.6093) 
(list 2805.415 676.0593) 
(list 2805.415 675.8823) 
(list 2879.4375 676.5323)))
(apply 'command (append '("pline") coords '("c")))
(setq currobj (ssadd (entlast) currobj))
(setq coords (list 
(list 2879.4375 676.3893) 
(list 2805.415 675.7393) 
(list 2805.415 675.5623) 
(list 2879.4375 676.3123)))
(apply 'command (append '("pline") coords '("c")))
(setq currobj (ssadd (entlast) currobj))
(command "_layer" "set" "nitride" "")
(command "_layer" "set" "text" "")
(command "_circle" "2879.0625,665.1693" "0.075")
(command "_circle" "2879.0625,665.4693" "0.075")
(command "_circle" "2879.0625,665.7693" "0.075")
(command "_circle" "2879.0625,666.0693" "0.075")
(command "_circle" "2879.0625,666.3693" "0.075")
(command "_circle" "2878.7625,665.1693" "0.075")
(command "_circle" "2878.7625,665.4693" "0.075")
(command "_circle" "2878.7625,665.7693" "0.075")
(command "_circle" "2878.7625,666.0693" "0.075")
(command "_circle" "2878.7625,666.3693" "0.075")
(command "_circle" "2878.4625,665.1693" "0.075")
(command "_circle" "2878.4625,665.4693" "0.075")
(command "_circle" "2878.4625,665.7693" "0.075")
(command "_circle" "2878.4625,666.0693" "0.075")
(command "_circle" "2878.4625,666.3693" "0.075")
(command "_circle" "2878.1625,665.1693" "0.075")
(command "_circle" "2878.1625,665.4693" "0.075")
(command "_circle" "2878.1625,665.7693" "0.075")
(command "_circle" "2878.1625,666.0693" "0.075")
(command "_circle" "2878.1625,666.3693" "0.075")
(command "_circle" "2877.8625,665.1693" "0.075")
(command "_circle" "2877.8625,665.4693" "0.075")
(command "_circle" "2877.8625,665.7693" "0.075")
(command "_circle" "2877.8625,666.0693" "0.075")
(command "_circle" "2877.8625,666.3693" "0.075")
(command "_layer" "set" "nitride" "")
(setq coords (list 
(list 2880.2625 690.6123) 
(list 2880.2625 806.257) 
(list 2879.7375 806.257) 
(list 2879.7375 690.6123)))
(apply 'command (append '("pline") coords '("c")))
(setq currobj (ssadd (entlast) currobj))
(command "_layer" "set" "prebias" "")
(command "_rectangle" "2879.7375,690.6123" "2880.2625,806.257")
(setq currobj (ssadd (entlast) currobj))
(command "_layer" "set" "nitride" "")
(setq coords (list 
(list 2880.2625 806.257) 
(list 2880.5625 816.257) 
(list 2880.5625 816.257) 
(list 2880.5625 817.257) 
(list 2954.585 816.507) 
(list 2954.585 821.45) 
(list 2880.5625 820.7) 
(list 2880.5625 821.7) 
(list 2880.5625 821.7) 
(list 2880.2625 831.7) 
(list 2879.7375 831.7) 
(list 2879.4375 821.7) 
(list 2879.4375 821.7) 
(list 2879.4375 820.7) 
(list 2805.415 821.45) 
(list 2805.415 816.507) 
(list 2879.4375 817.257) 
(list 2879.4375 816.257) 
(list 2879.4375 816.257) 
(list 2879.7375 806.257)))
(apply 'command (append '("pline") coords '("c")))
(setq currobj (ssadd (entlast) currobj))
(command "_layer" "set" "prebias" "")
(setq coords (list 
(list 2879.4375 806.257) 
(list 2879.4375 817.257) 
(list 2805.415 816.507) 
(list 2805.415 821.45) 
(list 2879.4375 820.7) 
(list 2879.4375 831.7) 
(list 2880.5625 831.7) 
(list 2880.5625 820.7) 
(list 2954.585 821.45) 
(list 2954.585 816.507) 
(list 2880.5625 817.257) 
(list 2880.5625 806.257)))
(apply 'command (append '("pline") coords '("c")))
(setq currobj (ssadd (entlast) currobj))
(command "_layer" "set" "nitride" "")
(command "_layer" "set" "fda1" "")
(setq coords (list 
(list 2880.5625 817.4) 
(list 2954.585 816.65) 
(list 2954.585 816.827) 
(list 2880.5625 817.477)))
(apply 'command (append '("pline") coords '("c")))
(setq currobj (ssadd (entlast) currobj))
(setq coords (list 
(list 2880.5625 817.62) 
(list 2954.585 816.97) 
(list 2954.585 817.147) 
(list 2880.5625 817.697)))
(apply 'command (append '("pline") coords '("c")))
(setq currobj (ssadd (entlast) currobj))
(setq coords (list 
(list 2880.5625 817.84) 
(list 2954.585 817.29) 
(list 2954.585 817.467) 
(list 2880.5625 817.917)))
(apply 'command (append '("pline") coords '("c")))
(setq currobj (ssadd (entlast) currobj))
(setq coords (list 
(list 2880.5625 818.06) 
(list 2954.585 817.61) 
(list 2954.585 817.787) 
(list 2880.5625 818.137)))
(apply 'command (append '("pline") coords '("c")))
(setq currobj (ssadd (entlast) currobj))
(setq coords (list 
(list 2880.5625 818.28) 
(list 2954.585 817.93) 
(list 2954.585 818.107) 
(list 2880.5625 818.357)))
(apply 'command (append '("pline") coords '("c")))
(setq currobj (ssadd (entlast) currobj))
(setq coords (list 
(list 2880.5625 818.5) 
(list 2954.585 818.25) 
(list 2954.585 818.427) 
(list 2880.5625 818.577)))
(apply 'command (append '("pline") coords '("c")))
(setq currobj (ssadd (entlast) currobj))
(setq coords (list 
(list 2880.5625 818.72) 
(list 2954.585 818.57) 
(list 2954.585 818.747) 
(list 2880.5625 818.797)))
(apply 'command (append '("pline") coords '("c")))
(setq currobj (ssadd (entlast) currobj))
(setq coords (list 
(list 2880.5625 818.94) 
(list 2954.585 818.89) 
(list 2954.585 819.067) 
(list 2880.5625 819.017)))
(apply 'command (append '("pline") coords '("c")))
(setq currobj (ssadd (entlast) currobj))
(setq coords (list 
(list 2880.5625 819.16) 
(list 2954.585 819.21) 
(list 2954.585 819.387) 
(list 2880.5625 819.237)))
(apply 'command (append '("pline") coords '("c")))
(setq currobj (ssadd (entlast) currobj))
(setq coords (list 
(list 2880.5625 819.38) 
(list 2954.585 819.53) 
(list 2954.585 819.707) 
(list 2880.5625 819.457)))
(apply 'command (append '("pline") coords '("c")))
(setq currobj (ssadd (entlast) currobj))
(setq coords (list 
(list 2880.5625 819.6) 
(list 2954.585 819.85) 
(list 2954.585 820.027) 
(list 2880.5625 819.677)))
(apply 'command (append '("pline") coords '("c")))
(setq currobj (ssadd (entlast) currobj))
(setq coords (list 
(list 2880.5625 819.82) 
(list 2954.585 820.17) 
(list 2954.585 820.347) 
(list 2880.5625 819.897)))
(apply 'command (append '("pline") coords '("c")))
(setq currobj (ssadd (entlast) currobj))
(setq coords (list 
(list 2880.5625 820.04) 
(list 2954.585 820.49) 
(list 2954.585 820.667) 
(list 2880.5625 820.117)))
(apply 'command (append '("pline") coords '("c")))
(setq currobj (ssadd (entlast) currobj))
(setq coords (list 
(list 2880.5625 820.26) 
(list 2954.585 820.81) 
(list 2954.585 820.987) 
(list 2880.5625 820.337)))
(apply 'command (append '("pline") coords '("c")))
(setq currobj (ssadd (entlast) currobj))
(setq coords (list 
(list 2880.5625 820.48) 
(list 2954.585 821.13) 
(list 2954.585 821.307) 
(list 2880.5625 820.557)))
(apply 'command (append '("pline") coords '("c")))
(setq currobj (ssadd (entlast) currobj))
(setq coords (list 
(list 2879.4375 820.557) 
(list 2805.415 821.307) 
(list 2805.415 821.13) 
(list 2879.4375 820.48)))
(apply 'command (append '("pline") coords '("c")))
(setq currobj (ssadd (entlast) currobj))
(setq coords (list 
(list 2879.4375 820.337) 
(list 2805.415 820.987) 
(list 2805.415 820.81) 
(list 2879.4375 820.26)))
(apply 'command (append '("pline") coords '("c")))
(setq currobj (ssadd (entlast) currobj))
(setq coords (list 
(list 2879.4375 820.117) 
(list 2805.415 820.667) 
(list 2805.415 820.49) 
(list 2879.4375 820.04)))
(apply 'command (append '("pline") coords '("c")))
(setq currobj (ssadd (entlast) currobj))
(setq coords (list 
(list 2879.4375 819.897) 
(list 2805.415 820.347) 
(list 2805.415 820.17) 
(list 2879.4375 819.82)))
(apply 'command (append '("pline") coords '("c")))
(setq currobj (ssadd (entlast) currobj))
(setq coords (list 
(list 2879.4375 819.677) 
(list 2805.415 820.027) 
(list 2805.415 819.85) 
(list 2879.4375 819.6)))
(apply 'command (append '("pline") coords '("c")))
(setq currobj (ssadd (entlast) currobj))
(setq coords (list 
(list 2879.4375 819.457) 
(list 2805.415 819.707) 
(list 2805.415 819.53) 
(list 2879.4375 819.38)))
(apply 'command (append '("pline") coords '("c")))
(setq currobj (ssadd (entlast) currobj))
(setq coords (list 
(list 2879.4375 819.237) 
(list 2805.415 819.387) 
(list 2805.415 819.21) 
(list 2879.4375 819.16)))
(apply 'command (append '("pline") coords '("c")))
(setq currobj (ssadd (entlast) currobj))
(setq coords (list 
(list 2879.4375 819.017) 
(list 2805.415 819.067) 
(list 2805.415 818.89) 
(list 2879.4375 818.94)))
(apply 'command (append '("pline") coords '("c")))
(setq currobj (ssadd (entlast) currobj))
(setq coords (list 
(list 2879.4375 818.797) 
(list 2805.415 818.747) 
(list 2805.415 818.57) 
(list 2879.4375 818.72)))
(apply 'command (append '("pline") coords '("c")))
(setq currobj (ssadd (entlast) currobj))
(setq coords (list 
(list 2879.4375 818.577) 
(list 2805.415 818.427) 
(list 2805.415 818.25) 
(list 2879.4375 818.5)))
(apply 'command (append '("pline") coords '("c")))
(setq currobj (ssadd (entlast) currobj))
(setq coords (list 
(list 2879.4375 818.357) 
(list 2805.415 818.107) 
(list 2805.415 817.93) 
(list 2879.4375 818.28)))
(apply 'command (append '("pline") coords '("c")))
(setq currobj (ssadd (entlast) currobj))
(setq coords (list 
(list 2879.4375 818.137) 
(list 2805.415 817.787) 
(list 2805.415 817.61) 
(list 2879.4375 818.06)))
(apply 'command (append '("pline") coords '("c")))
(setq currobj (ssadd (entlast) currobj))
(setq coords (list 
(list 2879.4375 817.917) 
(list 2805.415 817.467) 
(list 2805.415 817.29) 
(list 2879.4375 817.84)))
(apply 'command (append '("pline") coords '("c")))
(setq currobj (ssadd (entlast) currobj))
(setq coords (list 
(list 2879.4375 817.697) 
(list 2805.415 817.147) 
(list 2805.415 816.97) 
(list 2879.4375 817.62)))
(apply 'command (append '("pline") coords '("c")))
(setq currobj (ssadd (entlast) currobj))
(setq coords (list 
(list 2879.4375 817.477) 
(list 2805.415 816.827) 
(list 2805.415 816.65) 
(list 2879.4375 817.4)))
(apply 'command (append '("pline") coords '("c")))
(setq currobj (ssadd (entlast) currobj))
(command "_layer" "set" "nitride" "")
(command "_layer" "set" "text" "")
(command "_circle" "2879.0625,806.257" "0.075")
(command "_circle" "2879.0625,806.557" "0.075")
(command "_circle" "2879.0625,806.857" "0.075")
(command "_circle" "2879.0625,807.157" "0.075")
(command "_circle" "2879.0625,807.457" "0.075")
(command "_circle" "2878.7625,806.257" "0.075")
(command "_circle" "2878.7625,806.557" "0.075")
(command "_circle" "2878.7625,806.857" "0.075")
(command "_circle" "2878.7625,807.157" "0.075")
(command "_circle" "2878.7625,807.457" "0.075")
(command "_circle" "2878.4625,806.257" "0.075")
(command "_circle" "2878.4625,806.557" "0.075")
(command "_circle" "2878.4625,806.857" "0.075")
(command "_circle" "2878.4625,807.157" "0.075")
(command "_circle" "2878.4625,807.457" "0.075")
(command "_circle" "2878.1625,806.257" "0.075")
(command "_circle" "2878.1625,806.557" "0.075")
(command "_circle" "2878.1625,806.857" "0.075")
(command "_circle" "2878.1625,807.157" "0.075")
(command "_circle" "2878.1625,807.457" "0.075")
(command "_circle" "2877.8625,806.257" "0.075")
(command "_circle" "2877.8625,806.557" "0.075")
(command "_circle" "2877.8625,806.857" "0.075")
(command "_circle" "2877.8625,807.157" "0.075")
(command "_circle" "2877.8625,807.457" "0.075")
(command "_layer" "set" "nitride" "")
(setq coords (list 
(list 2880.2625 831.7) 
(list 2880.2625 836.7) 
(list 2879.7375 836.7) 
(list 2879.7375 831.7)))
(apply 'command (append '("pline") coords '("c")))
(setq currobj (ssadd (entlast) currobj))
(command "_layer" "set" "prebias" "")
(command "_rectangle" "2879.7375,831.7" "2880.2625,836.7")
(setq currobj (ssadd (entlast) currobj))
(command "_layer" "set" "nitride" "")
(setq cooledsinglenanobeam9 currobj)
(setq currobj nil)
(setq currobj (ssadd))
; DRAWING PHOTONIC CRYSTAL
(command "_layer" "set" "negYjunc" "")
(setq coords (list 
(list 2880.135 866.7) 
(list 2880 851.7) 
(list 2880 866.7)))
(apply 'command (append '("pline") coords '("c")))
(setq currobj (ssadd (entlast) currobj))
(setq coords (list 
(list 2880.2625 836.7) 
(list 2880.415 866.7) 
(list 2881.086 866.7) 
(list 2881.086 836.7)))
(apply 'command (append '("pline") coords '("c")))
(setq currobj (ssadd (entlast) currobj))
(setq coords (list 
(list 2879.865 866.7) 
(list 2880 851.7) 
(list 2880 866.7)))
(apply 'command (append '("pline") coords '("c")))
(setq currobj (ssadd (entlast) currobj))
(setq coords (list 
(list 2879.7375 836.7) 
(list 2879.585 866.7) 
(list 2878.914 866.7) 
(list 2878.914 836.7)))
(apply 'command (append '("pline") coords '("c")))
(setq currobj (ssadd (entlast) currobj))
(command "_layer" "set" "nitride" "")
(setq yjunction9 currobj)
(setq currobj nil)
(setq currobj (ssadd))
(setq tap9 nil)
(setq tap9 (ssadd))
(command "_layer" "set" "phc" "")
(setq coords (list 
(list 2880 866.7) 
(list 2880.135 866.7) 
(list 2880.135 866.7103) 
(list 2880.135 866.7206) 
(list 2880.135 866.7308) 
(list 2880.135 866.7411) 
(list 2880.135 866.7514) 
(list 2880.135 866.7617) 
(list 2880.135 866.7719) 
(list 2880.135 866.7822) 
(list 2880.135 866.7925) 
(list 2880.135 866.8028) 
(list 2880.135 866.8131) 
(list 2880.135 866.8233) 
(list 2880.135 866.8336) 
(list 2880.135 866.8439) 
(list 2880.135 866.8542) 
(list 2880.135 866.8644) 
(list 2880.135 866.8747) 
(list 2880.135 866.885) 
(list 2880.135 866.8953) 
(list 2880.135 866.9056) 
(list 2880.135 866.9158) 
(list 2880.135 866.9261) 
(list 2880.135 866.9364) 
(list 2880.135 866.9467) 
(list 2880.135 866.9569) 
(list 2880.135 866.9672) 
(list 2880.135 866.9775) 
(list 2880.135 866.9878) 
(list 2880.135 866.9981) 
(list 2880.135 867.0083) 
(list 2880.135 867.0186) 
(list 2880.135 867.0289) 
(list 2880.135 867.0392) 
(list 2880.135 867.0494) 
(list 2880.135 867.0597) 
(list 2880.135 867.07) 
(list 2880 867.07)))
(apply 'command (append '("pline") coords '("c")))
(setq tap9 (ssadd (entlast) tap9))
(command "_mirror" (entlast) "" "2880,900" "2880,901" "No")
(setq tap9 (ssadd (entlast) tap9))
(setq coords (list 
(list 2880.4235 866.7) 
(list 2880.415 866.7) 
(list 2880.4152 866.7103) 
(list 2880.4154 866.7206) 
(list 2880.4156 866.7308) 
(list 2880.4157 866.7411) 
(list 2880.4158 866.7514) 
(list 2880.4157 866.7617) 
(list 2880.4156 866.7719) 
(list 2880.4154 866.7822) 
(list 2880.4151 866.7925) 
(list 2880.4147 866.8028) 
(list 2880.4143 866.8131) 
(list 2880.4138 866.8233) 
(list 2880.4133 866.8336) 
(list 2880.4127 866.8439) 
(list 2880.4122 866.8542) 
(list 2880.4118 866.8644) 
(list 2880.4114 866.8747) 
(list 2880.4111 866.885) 
(list 2880.411 866.8953) 
(list 2880.411 866.9056) 
(list 2880.4111 866.9158) 
(list 2880.4114 866.9261) 
(list 2880.4119 866.9364) 
(list 2880.4126 866.9467) 
(list 2880.4133 866.9569) 
(list 2880.4143 866.9672) 
(list 2880.4153 866.9775) 
(list 2880.4164 866.9878) 
(list 2880.4176 866.9981) 
(list 2880.4187 867.0083) 
(list 2880.4198 867.0186) 
(list 2880.4209 867.0289) 
(list 2880.4218 867.0392) 
(list 2880.4226 867.0494) 
(list 2880.4232 867.0597) 
(list 2880.4235 867.07) 
(list 2880.4235 867.07)))
(apply 'command (append '("pline") coords '("c")))
(setq tap9 (ssadd (entlast) tap9))
(command "_mirror" (entlast) "" "2880,900" "2880,901" "No")
(setq tap9 (ssadd (entlast) tap9))
(setq coords (list 
(list 2881.086 866.7) 
(list 2880.4235 866.7) 
(list 2880.4235 866.7103) 
(list 2880.4235 866.7206) 
(list 2880.4235 866.7308) 
(list 2880.4235 866.7411) 
(list 2880.4235 866.7514) 
(list 2880.4235 866.7617) 
(list 2880.4235 866.7719) 
(list 2880.4235 866.7822) 
(list 2880.4235 866.7925) 
(list 2880.4235 866.8028) 
(list 2880.4235 866.8131) 
(list 2880.4235 866.8233) 
(list 2880.4235 866.8336) 
(list 2880.4235 866.8439) 
(list 2880.4235 866.8542) 
(list 2880.4235 866.8644) 
(list 2880.4235 866.8747) 
(list 2880.4235 866.885) 
(list 2880.4235 866.8953) 
(list 2880.4235 866.9056) 
(list 2880.4235 866.9158) 
(list 2880.4235 866.9261) 
(list 2880.4235 866.9364) 
(list 2880.4235 866.9467) 
(list 2880.4235 866.9569) 
(list 2880.4235 866.9672) 
(list 2880.4235 866.9775) 
(list 2880.4235 866.9878) 
(list 2880.4235 866.9981) 
(list 2880.4235 867.0083) 
(list 2880.4235 867.0186) 
(list 2880.4235 867.0289) 
(list 2880.4235 867.0392) 
(list 2880.4235 867.0494) 
(list 2880.4235 867.0597) 
(list 2880.4235 867.07) 
(list 2881.086 867.07)))
(apply 'command (append '("pline") coords '("c")))
(setq tap9 (ssadd (entlast) tap9))
(command "_mirror" (entlast) "" "2880,900" "2880,901" "No")
(setq tap9 (ssadd (entlast) tap9))
(setq coords (list 
(list 2880 867.07) 
(list 2880.135 867.07) 
(list 2880.135 867.0803) 
(list 2880.135 867.0906) 
(list 2880.135 867.1008) 
(list 2880.135 867.1111) 
(list 2880.135 867.1214) 
(list 2880.135 867.1317) 
(list 2880.135 867.1419) 
(list 2880.135 867.1522) 
(list 2880.135 867.1625) 
(list 2880.135 867.1728) 
(list 2880.135 867.1831) 
(list 2880.135 867.1933) 
(list 2880.135 867.2036) 
(list 2880.135 867.2139) 
(list 2880.135 867.2242) 
(list 2880.135 867.2344) 
(list 2880.135 867.2447) 
(list 2880.135 867.255) 
(list 2880.135 867.2653) 
(list 2880.135 867.2756) 
(list 2880.135 867.2858) 
(list 2880.135 867.2961) 
(list 2880.135 867.3064) 
(list 2880.135 867.3167) 
(list 2880.135 867.3269) 
(list 2880.135 867.3372) 
(list 2880.135 867.3475) 
(list 2880.135 867.3578) 
(list 2880.135 867.3681) 
(list 2880.135 867.3783) 
(list 2880.135 867.3886) 
(list 2880.135 867.3989) 
(list 2880.135 867.4092) 
(list 2880.135 867.4194) 
(list 2880.135 867.4297) 
(list 2880.135 867.44) 
(list 2880 867.44)))
(apply 'command (append '("pline") coords '("c")))
(setq tap9 (ssadd (entlast) tap9))
(command "_mirror" (entlast) "" "2880,900" "2880,901" "No")
(setq tap9 (ssadd (entlast) tap9))
(setq coords (list 
(list 2880.4321 867.07) 
(list 2880.4235 867.07) 
(list 2880.4236 867.0803) 
(list 2880.4235 867.0906) 
(list 2880.4231 867.1008) 
(list 2880.4224 867.1111) 
(list 2880.4214 867.1214) 
(list 2880.4202 867.1317) 
(list 2880.4188 867.1419) 
(list 2880.4172 867.1522) 
(list 2880.4155 867.1625) 
(list 2880.4137 867.1728) 
(list 2880.4119 867.1831) 
(list 2880.4101 867.1933) 
(list 2880.4084 867.2036) 
(list 2880.4069 867.2139) 
(list 2880.4056 867.2242) 
(list 2880.4045 867.2344) 
(list 2880.4038 867.2447) 
(list 2880.4034 867.255) 
(list 2880.4034 867.2653) 
(list 2880.4037 867.2756) 
(list 2880.4045 867.2858) 
(list 2880.4056 867.2961) 
(list 2880.4071 867.3064) 
(list 2880.4089 867.3167) 
(list 2880.411 867.3269) 
(list 2880.4133 867.3372) 
(list 2880.4157 867.3475) 
(list 2880.4182 867.3578) 
(list 2880.4207 867.3681) 
(list 2880.4232 867.3783) 
(list 2880.4255 867.3886) 
(list 2880.4275 867.3989) 
(list 2880.4293 867.4092) 
(list 2880.4306 867.4194) 
(list 2880.4316 867.4297) 
(list 2880.4321 867.44) 
(list 2880.4321 867.44)))
(apply 'command (append '("pline") coords '("c")))
(setq tap9 (ssadd (entlast) tap9))
(command "_mirror" (entlast) "" "2880,900" "2880,901" "No")
(setq tap9 (ssadd (entlast) tap9))
(setq coords (list 
(list 2881.086 867.07) 
(list 2880.4321 867.07) 
(list 2880.4321 867.0803) 
(list 2880.4321 867.0906) 
(list 2880.4321 867.1008) 
(list 2880.4321 867.1111) 
(list 2880.4321 867.1214) 
(list 2880.4321 867.1317) 
(list 2880.4321 867.1419) 
(list 2880.4321 867.1522) 
(list 2880.4321 867.1625) 
(list 2880.4321 867.1728) 
(list 2880.4321 867.1831) 
(list 2880.4321 867.1933) 
(list 2880.4321 867.2036) 
(list 2880.4321 867.2139) 
(list 2880.4321 867.2242) 
(list 2880.4321 867.2344) 
(list 2880.4321 867.2447) 
(list 2880.4321 867.255) 
(list 2880.4321 867.2653) 
(list 2880.4321 867.2756) 
(list 2880.4321 867.2858) 
(list 2880.4321 867.2961) 
(list 2880.4321 867.3064) 
(list 2880.4321 867.3167) 
(list 2880.4321 867.3269) 
(list 2880.4321 867.3372) 
(list 2880.4321 867.3475) 
(list 2880.4321 867.3578) 
(list 2880.4321 867.3681) 
(list 2880.4321 867.3783) 
(list 2880.4321 867.3886) 
(list 2880.4321 867.3989) 
(list 2880.4321 867.4092) 
(list 2880.4321 867.4194) 
(list 2880.4321 867.4297) 
(list 2880.4321 867.44) 
(list 2881.086 867.44)))
(apply 'command (append '("pline") coords '("c")))
(setq tap9 (ssadd (entlast) tap9))
(command "_mirror" (entlast) "" "2880,900" "2880,901" "No")
(setq tap9 (ssadd (entlast) tap9))
(setq coords (list 
(list 2880 867.44) 
(list 2880.135 867.44) 
(list 2880.135 867.4503) 
(list 2880.135 867.4606) 
(list 2880.135 867.4708) 
(list 2880.135 867.4811) 
(list 2880.135 867.4914) 
(list 2880.135 867.5017) 
(list 2880.135 867.5119) 
(list 2880.135 867.5222) 
(list 2880.135 867.5325) 
(list 2880.135 867.5428) 
(list 2880.135 867.5531) 
(list 2880.135 867.5633) 
(list 2880.135 867.5736) 
(list 2880.135 867.5839) 
(list 2880.135 867.5942) 
(list 2880.135 867.6044) 
(list 2880.135 867.6147) 
(list 2880.135 867.625) 
(list 2880.135 867.6353) 
(list 2880.135 867.6456) 
(list 2880.135 867.6558) 
(list 2880.135 867.6661) 
(list 2880.135 867.6764) 
(list 2880.135 867.6867) 
(list 2880.135 867.6969) 
(list 2880.135 867.7072) 
(list 2880.135 867.7175) 
(list 2880.135 867.7278) 
(list 2880.135 867.7381) 
(list 2880.135 867.7483) 
(list 2880.135 867.7586) 
(list 2880.135 867.7689) 
(list 2880.135 867.7792) 
(list 2880.135 867.7894) 
(list 2880.135 867.7997) 
(list 2880.135 867.81) 
(list 2880 867.81)))
(apply 'command (append '("pline") coords '("c")))
(setq tap9 (ssadd (entlast) tap9))
(command "_mirror" (entlast) "" "2880,900" "2880,901" "No")
(setq tap9 (ssadd (entlast) tap9))
(setq coords (list 
(list 2880.4406 867.44) 
(list 2880.4321 867.44) 
(list 2880.4321 867.4503) 
(list 2880.4315 867.4606) 
(list 2880.4305 867.4708) 
(list 2880.429 867.4811) 
(list 2880.427 867.4914) 
(list 2880.4247 867.5017) 
(list 2880.422 867.5119) 
(list 2880.419 867.5222) 
(list 2880.4159 867.5325) 
(list 2880.4127 867.5428) 
(list 2880.4095 867.5531) 
(list 2880.4064 867.5633) 
(list 2880.4036 867.5736) 
(list 2880.4011 867.5839) 
(list 2880.3989 867.5942) 
(list 2880.3973 867.6044) 
(list 2880.3962 867.6147) 
(list 2880.3957 867.625) 
(list 2880.3958 867.6353) 
(list 2880.3965 867.6456) 
(list 2880.3978 867.6558) 
(list 2880.3998 867.6661) 
(list 2880.4023 867.6764) 
(list 2880.4052 867.6867) 
(list 2880.4086 867.6969) 
(list 2880.4122 867.7072) 
(list 2880.4161 867.7175) 
(list 2880.42 867.7278) 
(list 2880.4239 867.7381) 
(list 2880.4277 867.7483) 
(list 2880.4311 867.7586) 
(list 2880.4342 867.7689) 
(list 2880.4367 867.7792) 
(list 2880.4387 867.7894) 
(list 2880.44 867.7997) 
(list 2880.4406 867.81) 
(list 2880.4406 867.81)))
(apply 'command (append '("pline") coords '("c")))
(setq tap9 (ssadd (entlast) tap9))
(command "_mirror" (entlast) "" "2880,900" "2880,901" "No")
(setq tap9 (ssadd (entlast) tap9))
(setq coords (list 
(list 2881.086 867.44) 
(list 2880.4406 867.44) 
(list 2880.4406 867.4503) 
(list 2880.4406 867.4606) 
(list 2880.4406 867.4708) 
(list 2880.4406 867.4811) 
(list 2880.4406 867.4914) 
(list 2880.4406 867.5017) 
(list 2880.4406 867.5119) 
(list 2880.4406 867.5222) 
(list 2880.4406 867.5325) 
(list 2880.4406 867.5428) 
(list 2880.4406 867.5531) 
(list 2880.4406 867.5633) 
(list 2880.4406 867.5736) 
(list 2880.4406 867.5839) 
(list 2880.4406 867.5942) 
(list 2880.4406 867.6044) 
(list 2880.4406 867.6147) 
(list 2880.4406 867.625) 
(list 2880.4406 867.6353) 
(list 2880.4406 867.6456) 
(list 2880.4406 867.6558) 
(list 2880.4406 867.6661) 
(list 2880.4406 867.6764) 
(list 2880.4406 867.6867) 
(list 2880.4406 867.6969) 
(list 2880.4406 867.7072) 
(list 2880.4406 867.7175) 
(list 2880.4406 867.7278) 
(list 2880.4406 867.7381) 
(list 2880.4406 867.7483) 
(list 2880.4406 867.7586) 
(list 2880.4406 867.7689) 
(list 2880.4406 867.7792) 
(list 2880.4406 867.7894) 
(list 2880.4406 867.7997) 
(list 2880.4406 867.81) 
(list 2881.086 867.81)))
(apply 'command (append '("pline") coords '("c")))
(setq tap9 (ssadd (entlast) tap9))
(command "_mirror" (entlast) "" "2880,900" "2880,901" "No")
(setq tap9 (ssadd (entlast) tap9))
(setq coords (list 
(list 2880 867.81) 
(list 2880.135 867.81) 
(list 2880.135 867.8203) 
(list 2880.135 867.8306) 
(list 2880.135 867.8408) 
(list 2880.135 867.8511) 
(list 2880.135 867.8614) 
(list 2880.135 867.8717) 
(list 2880.135 867.8819) 
(list 2880.135 867.8922) 
(list 2880.135 867.9025) 
(list 2880.135 867.9128) 
(list 2880.135 867.9231) 
(list 2880.135 867.9333) 
(list 2880.135 867.9436) 
(list 2880.135 867.9539) 
(list 2880.135 867.9642) 
(list 2880.135 867.9744) 
(list 2880.135 867.9847) 
(list 2880.135 867.995) 
(list 2880.135 868.0053) 
(list 2880.135 868.0156) 
(list 2880.135 868.0258) 
(list 2880.135 868.0361) 
(list 2880.135 868.0464) 
(list 2880.135 868.0567) 
(list 2880.135 868.0669) 
(list 2880.135 868.0772) 
(list 2880.135 868.0875) 
(list 2880.135 868.0978) 
(list 2880.135 868.1081) 
(list 2880.135 868.1183) 
(list 2880.135 868.1286) 
(list 2880.135 868.1389) 
(list 2880.135 868.1492) 
(list 2880.135 868.1594) 
(list 2880.135 868.1697) 
(list 2880.135 868.18) 
(list 2880 868.18)))
(apply 'command (append '("pline") coords '("c")))
(setq tap9 (ssadd (entlast) tap9))
(command "_mirror" (entlast) "" "2880,900" "2880,901" "No")
(setq tap9 (ssadd (entlast) tap9))
(setq coords (list 
(list 2880.4491 867.81) 
(list 2880.4406 867.81) 
(list 2880.4405 867.8203) 
(list 2880.4396 867.8306) 
(list 2880.438 867.8408) 
(list 2880.4356 867.8511) 
(list 2880.4327 867.8614) 
(list 2880.4291 867.8717) 
(list 2880.4252 867.8819) 
(list 2880.4208 867.8922) 
(list 2880.4163 867.9025) 
(list 2880.4117 867.9128) 
(list 2880.4071 867.9231) 
(list 2880.4028 867.9333) 
(list 2880.3988 867.9436) 
(list 2880.3952 867.9539) 
(list 2880.3923 867.9642) 
(list 2880.3901 867.9744) 
(list 2880.3886 867.9847) 
(list 2880.3879 867.995) 
(list 2880.3882 868.0053) 
(list 2880.3892 868.0156) 
(list 2880.3912 868.0258) 
(list 2880.3939 868.0361) 
(list 2880.3974 868.0464) 
(list 2880.4016 868.0567) 
(list 2880.4062 868.0669) 
(list 2880.4112 868.0772) 
(list 2880.4165 868.0875) 
(list 2880.4218 868.0978) 
(list 2880.4271 868.1081) 
(list 2880.4321 868.1183) 
(list 2880.4367 868.1286) 
(list 2880.4408 868.1389) 
(list 2880.4442 868.1492) 
(list 2880.4467 868.1594) 
(list 2880.4484 868.1697) 
(list 2880.4491 868.18) 
(list 2880.4491 868.18)))
(apply 'command (append '("pline") coords '("c")))
(setq tap9 (ssadd (entlast) tap9))
(command "_mirror" (entlast) "" "2880,900" "2880,901" "No")
(setq tap9 (ssadd (entlast) tap9))
(setq coords (list 
(list 2881.086 867.81) 
(list 2880.4491 867.81) 
(list 2880.4491 867.8203) 
(list 2880.4491 867.8306) 
(list 2880.4491 867.8408) 
(list 2880.4491 867.8511) 
(list 2880.4491 867.8614) 
(list 2880.4491 867.8717) 
(list 2880.4491 867.8819) 
(list 2880.4491 867.8922) 
(list 2880.4491 867.9025) 
(list 2880.4491 867.9128) 
(list 2880.4491 867.9231) 
(list 2880.4491 867.9333) 
(list 2880.4491 867.9436) 
(list 2880.4491 867.9539) 
(list 2880.4491 867.9642) 
(list 2880.4491 867.9744) 
(list 2880.4491 867.9847) 
(list 2880.4491 867.995) 
(list 2880.4491 868.0053) 
(list 2880.4491 868.0156) 
(list 2880.4491 868.0258) 
(list 2880.4491 868.0361) 
(list 2880.4491 868.0464) 
(list 2880.4491 868.0567) 
(list 2880.4491 868.0669) 
(list 2880.4491 868.0772) 
(list 2880.4491 868.0875) 
(list 2880.4491 868.0978) 
(list 2880.4491 868.1081) 
(list 2880.4491 868.1183) 
(list 2880.4491 868.1286) 
(list 2880.4491 868.1389) 
(list 2880.4491 868.1492) 
(list 2880.4491 868.1594) 
(list 2880.4491 868.1697) 
(list 2880.4491 868.18) 
(list 2881.086 868.18)))
(apply 'command (append '("pline") coords '("c")))
(setq tap9 (ssadd (entlast) tap9))
(command "_mirror" (entlast) "" "2880,900" "2880,901" "No")
(setq tap9 (ssadd (entlast) tap9))
(setq coords (list 
(list 2880 868.18) 
(list 2880.135 868.18) 
(list 2880.135 868.1903) 
(list 2880.135 868.2006) 
(list 2880.135 868.2108) 
(list 2880.135 868.2211) 
(list 2880.135 868.2314) 
(list 2880.135 868.2417) 
(list 2880.135 868.2519) 
(list 2880.135 868.2622) 
(list 2880.135 868.2725) 
(list 2880.135 868.2828) 
(list 2880.135 868.2931) 
(list 2880.135 868.3033) 
(list 2880.135 868.3136) 
(list 2880.135 868.3239) 
(list 2880.135 868.3342) 
(list 2880.135 868.3444) 
(list 2880.135 868.3547) 
(list 2880.135 868.365) 
(list 2880.135 868.3753) 
(list 2880.135 868.3856) 
(list 2880.135 868.3958) 
(list 2880.135 868.4061) 
(list 2880.135 868.4164) 
(list 2880.135 868.4267) 
(list 2880.135 868.4369) 
(list 2880.135 868.4472) 
(list 2880.135 868.4575) 
(list 2880.135 868.4678) 
(list 2880.135 868.4781) 
(list 2880.135 868.4883) 
(list 2880.135 868.4986) 
(list 2880.135 868.5089) 
(list 2880.135 868.5192) 
(list 2880.135 868.5294) 
(list 2880.135 868.5397) 
(list 2880.135 868.55) 
(list 2880 868.55)))
(apply 'command (append '("pline") coords '("c")))
(setq tap9 (ssadd (entlast) tap9))
(command "_mirror" (entlast) "" "2880,900" "2880,901" "No")
(setq tap9 (ssadd (entlast) tap9))
(setq coords (list 
(list 2880.4577 868.18) 
(list 2880.4491 868.18) 
(list 2880.4489 868.1903) 
(list 2880.4476 868.2006) 
(list 2880.4454 868.2108) 
(list 2880.4423 868.2211) 
(list 2880.4383 868.2314) 
(list 2880.4336 868.2417) 
(list 2880.4283 868.2519) 
(list 2880.4227 868.2622) 
(list 2880.4167 868.2725) 
(list 2880.4107 868.2828) 
(list 2880.4047 868.2931) 
(list 2880.3991 868.3033) 
(list 2880.3939 868.3136) 
(list 2880.3894 868.3239) 
(list 2880.3857 868.3342) 
(list 2880.3828 868.3444) 
(list 2880.381 868.3547) 
(list 2880.3802 868.365) 
(list 2880.3805 868.3753) 
(list 2880.382 868.3856) 
(list 2880.3846 868.3958) 
(list 2880.3881 868.4061) 
(list 2880.3926 868.4164) 
(list 2880.3979 868.4267) 
(list 2880.4038 868.4369) 
(list 2880.4102 868.4472) 
(list 2880.4169 868.4575) 
(list 2880.4237 868.4678) 
(list 2880.4303 868.4781) 
(list 2880.4366 868.4883) 
(list 2880.4424 868.4986) 
(list 2880.4474 868.5089) 
(list 2880.4516 868.5192) 
(list 2880.4548 868.5294) 
(list 2880.4568 868.5397) 
(list 2880.4577 868.55) 
(list 2880.4577 868.55)))
(apply 'command (append '("pline") coords '("c")))
(setq tap9 (ssadd (entlast) tap9))
(command "_mirror" (entlast) "" "2880,900" "2880,901" "No")
(setq tap9 (ssadd (entlast) tap9))
(setq coords (list 
(list 2881.086 868.18) 
(list 2880.4577 868.18) 
(list 2880.4577 868.1903) 
(list 2880.4577 868.2006) 
(list 2880.4577 868.2108) 
(list 2880.4577 868.2211) 
(list 2880.4577 868.2314) 
(list 2880.4577 868.2417) 
(list 2880.4577 868.2519) 
(list 2880.4577 868.2622) 
(list 2880.4577 868.2725) 
(list 2880.4577 868.2828) 
(list 2880.4577 868.2931) 
(list 2880.4577 868.3033) 
(list 2880.4577 868.3136) 
(list 2880.4577 868.3239) 
(list 2880.4577 868.3342) 
(list 2880.4577 868.3444) 
(list 2880.4577 868.3547) 
(list 2880.4577 868.365) 
(list 2880.4577 868.3753) 
(list 2880.4577 868.3856) 
(list 2880.4577 868.3958) 
(list 2880.4577 868.4061) 
(list 2880.4577 868.4164) 
(list 2880.4577 868.4267) 
(list 2880.4577 868.4369) 
(list 2880.4577 868.4472) 
(list 2880.4577 868.4575) 
(list 2880.4577 868.4678) 
(list 2880.4577 868.4781) 
(list 2880.4577 868.4883) 
(list 2880.4577 868.4986) 
(list 2880.4577 868.5089) 
(list 2880.4577 868.5192) 
(list 2880.4577 868.5294) 
(list 2880.4577 868.5397) 
(list 2880.4577 868.55) 
(list 2881.086 868.55)))
(apply 'command (append '("pline") coords '("c")))
(setq tap9 (ssadd (entlast) tap9))
(command "_mirror" (entlast) "" "2880,900" "2880,901" "No")
(setq tap9 (ssadd (entlast) tap9))
(setq coords (list 
(list 2880 868.55) 
(list 2880.135 868.55) 
(list 2880.135 868.5603) 
(list 2880.135 868.5706) 
(list 2880.135 868.5808) 
(list 2880.135 868.5911) 
(list 2880.135 868.6014) 
(list 2880.135 868.6117) 
(list 2880.135 868.6219) 
(list 2880.135 868.6322) 
(list 2880.135 868.6425) 
(list 2880.135 868.6528) 
(list 2880.135 868.6631) 
(list 2880.135 868.6733) 
(list 2880.135 868.6836) 
(list 2880.135 868.6939) 
(list 2880.135 868.7042) 
(list 2880.135 868.7144) 
(list 2880.135 868.7247) 
(list 2880.135 868.735) 
(list 2880.135 868.7453) 
(list 2880.135 868.7556) 
(list 2880.135 868.7658) 
(list 2880.135 868.7761) 
(list 2880.135 868.7864) 
(list 2880.135 868.7967) 
(list 2880.135 868.8069) 
(list 2880.135 868.8172) 
(list 2880.135 868.8275) 
(list 2880.135 868.8378) 
(list 2880.135 868.8481) 
(list 2880.135 868.8583) 
(list 2880.135 868.8686) 
(list 2880.135 868.8789) 
(list 2880.135 868.8892) 
(list 2880.135 868.8994) 
(list 2880.135 868.9097) 
(list 2880.135 868.92) 
(list 2880 868.92)))
(apply 'command (append '("pline") coords '("c")))
(setq tap9 (ssadd (entlast) tap9))
(command "_mirror" (entlast) "" "2880,900" "2880,901" "No")
(setq tap9 (ssadd (entlast) tap9))
(setq coords (list 
(list 2880.4662 868.55) 
(list 2880.4577 868.55) 
(list 2880.4573 868.5603) 
(list 2880.4557 868.5706) 
(list 2880.4528 868.5808) 
(list 2880.4489 868.5911) 
(list 2880.4439 868.6014) 
(list 2880.4381 868.6117) 
(list 2880.4315 868.6219) 
(list 2880.4245 868.6322) 
(list 2880.4171 868.6425) 
(list 2880.4097 868.6528) 
(list 2880.4024 868.6631) 
(list 2880.3954 868.6733) 
(list 2880.3891 868.6836) 
(list 2880.3836 868.6939) 
(list 2880.379 868.7042) 
(list 2880.3756 868.7144) 
(list 2880.3734 868.7247) 
(list 2880.3725 868.735) 
(list 2880.3729 868.7453) 
(list 2880.3748 868.7556) 
(list 2880.3779 868.7658) 
(list 2880.3823 868.7761) 
(list 2880.3878 868.7864) 
(list 2880.3942 868.7967) 
(list 2880.4014 868.8069) 
(list 2880.4092 868.8172) 
(list 2880.4173 868.8275) 
(list 2880.4255 868.8378) 
(list 2880.4335 868.8481) 
(list 2880.4411 868.8583) 
(list 2880.448 868.8686) 
(list 2880.454 868.8789) 
(list 2880.459 868.8892) 
(list 2880.4628 868.8994) 
(list 2880.4652 868.9097) 
(list 2880.4662 868.92) 
(list 2880.4662 868.92)))
(apply 'command (append '("pline") coords '("c")))
(setq tap9 (ssadd (entlast) tap9))
(command "_mirror" (entlast) "" "2880,900" "2880,901" "No")
(setq tap9 (ssadd (entlast) tap9))
(setq coords (list 
(list 2881.086 868.55) 
(list 2880.4662 868.55) 
(list 2880.4662 868.5603) 
(list 2880.4662 868.5706) 
(list 2880.4662 868.5808) 
(list 2880.4662 868.5911) 
(list 2880.4662 868.6014) 
(list 2880.4662 868.6117) 
(list 2880.4662 868.6219) 
(list 2880.4662 868.6322) 
(list 2880.4662 868.6425) 
(list 2880.4662 868.6528) 
(list 2880.4662 868.6631) 
(list 2880.4662 868.6733) 
(list 2880.4662 868.6836) 
(list 2880.4662 868.6939) 
(list 2880.4662 868.7042) 
(list 2880.4662 868.7144) 
(list 2880.4662 868.7247) 
(list 2880.4662 868.735) 
(list 2880.4662 868.7453) 
(list 2880.4662 868.7556) 
(list 2880.4662 868.7658) 
(list 2880.4662 868.7761) 
(list 2880.4662 868.7864) 
(list 2880.4662 868.7967) 
(list 2880.4662 868.8069) 
(list 2880.4662 868.8172) 
(list 2880.4662 868.8275) 
(list 2880.4662 868.8378) 
(list 2880.4662 868.8481) 
(list 2880.4662 868.8583) 
(list 2880.4662 868.8686) 
(list 2880.4662 868.8789) 
(list 2880.4662 868.8892) 
(list 2880.4662 868.8994) 
(list 2880.4662 868.9097) 
(list 2880.4662 868.92) 
(list 2881.086 868.92)))
(apply 'command (append '("pline") coords '("c")))
(setq tap9 (ssadd (entlast) tap9))
(command "_mirror" (entlast) "" "2880,900" "2880,901" "No")
(setq tap9 (ssadd (entlast) tap9))
(setq coords (list 
(list 2880 868.92) 
(list 2880.135 868.92) 
(list 2880.135 868.9303) 
(list 2880.135 868.9406) 
(list 2880.135 868.9508) 
(list 2880.135 868.9611) 
(list 2880.135 868.9714) 
(list 2880.135 868.9817) 
(list 2880.135 868.9919) 
(list 2880.135 869.0022) 
(list 2880.135 869.0125) 
(list 2880.135 869.0228) 
(list 2880.135 869.0331) 
(list 2880.135 869.0433) 
(list 2880.135 869.0536) 
(list 2880.135 869.0639) 
(list 2880.135 869.0742) 
(list 2880.135 869.0844) 
(list 2880.135 869.0947) 
(list 2880.135 869.105) 
(list 2880.135 869.1153) 
(list 2880.135 869.1256) 
(list 2880.135 869.1358) 
(list 2880.135 869.1461) 
(list 2880.135 869.1564) 
(list 2880.135 869.1667) 
(list 2880.135 869.1769) 
(list 2880.135 869.1872) 
(list 2880.135 869.1975) 
(list 2880.135 869.2078) 
(list 2880.135 869.2181) 
(list 2880.135 869.2283) 
(list 2880.135 869.2386) 
(list 2880.135 869.2489) 
(list 2880.135 869.2592) 
(list 2880.135 869.2694) 
(list 2880.135 869.2797) 
(list 2880.135 869.29) 
(list 2880 869.29)))
(apply 'command (append '("pline") coords '("c")))
(setq tap9 (ssadd (entlast) tap9))
(command "_mirror" (entlast) "" "2880,900" "2880,901" "No")
(setq tap9 (ssadd (entlast) tap9))
(setq coords (list 
(list 2880.4747 868.92) 
(list 2880.4662 868.92) 
(list 2880.4657 868.9303) 
(list 2880.4637 868.9406) 
(list 2880.4603 868.9508) 
(list 2880.4555 868.9611) 
(list 2880.4495 868.9714) 
(list 2880.4425 868.9817) 
(list 2880.4347 868.9919) 
(list 2880.4263 869.0022) 
(list 2880.4175 869.0125) 
(list 2880.4086 869.0228) 
(list 2880.4 869.0331) 
(list 2880.3918 869.0433) 
(list 2880.3843 869.0536) 
(list 2880.3778 869.0639) 
(list 2880.3724 869.0742) 
(list 2880.3683 869.0844) 
(list 2880.3657 869.0947) 
(list 2880.3647 869.105) 
(list 2880.3653 869.1153) 
(list 2880.3675 869.1256) 
(list 2880.3713 869.1358) 
(list 2880.3765 869.1461) 
(list 2880.3829 869.1564) 
(list 2880.3906 869.1667) 
(list 2880.3991 869.1769) 
(list 2880.4082 869.1872) 
(list 2880.4177 869.1975) 
(list 2880.4273 869.2078) 
(list 2880.4367 869.2181) 
(list 2880.4455 869.2283) 
(list 2880.4536 869.2386) 
(list 2880.4607 869.2489) 
(list 2880.4665 869.2592) 
(list 2880.4709 869.2694) 
(list 2880.4736 869.2797) 
(list 2880.4747 869.29) 
(list 2880.4747 869.29)))
(apply 'command (append '("pline") coords '("c")))
(setq tap9 (ssadd (entlast) tap9))
(command "_mirror" (entlast) "" "2880,900" "2880,901" "No")
(setq tap9 (ssadd (entlast) tap9))
(setq coords (list 
(list 2881.086 868.92) 
(list 2880.4747 868.92) 
(list 2880.4747 868.9303) 
(list 2880.4747 868.9406) 
(list 2880.4747 868.9508) 
(list 2880.4747 868.9611) 
(list 2880.4747 868.9714) 
(list 2880.4747 868.9817) 
(list 2880.4747 868.9919) 
(list 2880.4747 869.0022) 
(list 2880.4747 869.0125) 
(list 2880.4747 869.0228) 
(list 2880.4747 869.0331) 
(list 2880.4747 869.0433) 
(list 2880.4747 869.0536) 
(list 2880.4747 869.0639) 
(list 2880.4747 869.0742) 
(list 2880.4747 869.0844) 
(list 2880.4747 869.0947) 
(list 2880.4747 869.105) 
(list 2880.4747 869.1153) 
(list 2880.4747 869.1256) 
(list 2880.4747 869.1358) 
(list 2880.4747 869.1461) 
(list 2880.4747 869.1564) 
(list 2880.4747 869.1667) 
(list 2880.4747 869.1769) 
(list 2880.4747 869.1872) 
(list 2880.4747 869.1975) 
(list 2880.4747 869.2078) 
(list 2880.4747 869.2181) 
(list 2880.4747 869.2283) 
(list 2880.4747 869.2386) 
(list 2880.4747 869.2489) 
(list 2880.4747 869.2592) 
(list 2880.4747 869.2694) 
(list 2880.4747 869.2797) 
(list 2880.4747 869.29) 
(list 2881.086 869.29)))
(apply 'command (append '("pline") coords '("c")))
(setq tap9 (ssadd (entlast) tap9))
(command "_mirror" (entlast) "" "2880,900" "2880,901" "No")
(setq tap9 (ssadd (entlast) tap9))
(setq coords (list 
(list 2880 869.29) 
(list 2880.135 869.29) 
(list 2880.135 869.3003) 
(list 2880.135 869.3106) 
(list 2880.135 869.3208) 
(list 2880.135 869.3311) 
(list 2880.135 869.3414) 
(list 2880.135 869.3517) 
(list 2880.135 869.3619) 
(list 2880.135 869.3722) 
(list 2880.135 869.3825) 
(list 2880.135 869.3928) 
(list 2880.135 869.4031) 
(list 2880.135 869.4133) 
(list 2880.135 869.4236) 
(list 2880.135 869.4339) 
(list 2880.135 869.4442) 
(list 2880.135 869.4544) 
(list 2880.135 869.4647) 
(list 2880.135 869.475) 
(list 2880.135 869.4853) 
(list 2880.135 869.4956) 
(list 2880.135 869.5058) 
(list 2880.135 869.5161) 
(list 2880.135 869.5264) 
(list 2880.135 869.5367) 
(list 2880.135 869.5469) 
(list 2880.135 869.5572) 
(list 2880.135 869.5675) 
(list 2880.135 869.5778) 
(list 2880.135 869.5881) 
(list 2880.135 869.5983) 
(list 2880.135 869.6086) 
(list 2880.135 869.6189) 
(list 2880.135 869.6292) 
(list 2880.135 869.6394) 
(list 2880.135 869.6497) 
(list 2880.135 869.66) 
(list 2880 869.66)))
(apply 'command (append '("pline") coords '("c")))
(setq tap9 (ssadd (entlast) tap9))
(command "_mirror" (entlast) "" "2880,900" "2880,901" "No")
(setq tap9 (ssadd (entlast) tap9))
(setq coords (list 
(list 2880.4833 869.29) 
(list 2880.4747 869.29) 
(list 2880.4741 869.3003) 
(list 2880.4717 869.3106) 
(list 2880.4677 869.3208) 
(list 2880.4621 869.3311) 
(list 2880.4552 869.3414) 
(list 2880.447 869.3517) 
(list 2880.4379 869.3619) 
(list 2880.4281 869.3722) 
(list 2880.4179 869.3825) 
(list 2880.4076 869.3928) 
(list 2880.3976 869.4031) 
(list 2880.3881 869.4133) 
(list 2880.3795 869.4236) 
(list 2880.3719 869.4339) 
(list 2880.3657 869.4442) 
(list 2880.3611 869.4544) 
(list 2880.3581 869.4647) 
(list 2880.357 869.475) 
(list 2880.3577 869.4853) 
(list 2880.3603 869.4956) 
(list 2880.3646 869.5058) 
(list 2880.3706 869.5161) 
(list 2880.3781 869.5264) 
(list 2880.3869 869.5367) 
(list 2880.3967 869.5469) 
(list 2880.4072 869.5572) 
(list 2880.4181 869.5675) 
(list 2880.4291 869.5778) 
(list 2880.4398 869.5881) 
(list 2880.45 869.5983) 
(list 2880.4592 869.6086) 
(list 2880.4673 869.6189) 
(list 2880.4739 869.6292) 
(list 2880.4789 869.6394) 
(list 2880.482 869.6497) 
(list 2880.4833 869.66) 
(list 2880.4833 869.66)))
(apply 'command (append '("pline") coords '("c")))
(setq tap9 (ssadd (entlast) tap9))
(command "_mirror" (entlast) "" "2880,900" "2880,901" "No")
(setq tap9 (ssadd (entlast) tap9))
(setq coords (list 
(list 2881.086 869.29) 
(list 2880.4833 869.29) 
(list 2880.4833 869.3003) 
(list 2880.4833 869.3106) 
(list 2880.4833 869.3208) 
(list 2880.4833 869.3311) 
(list 2880.4833 869.3414) 
(list 2880.4833 869.3517) 
(list 2880.4833 869.3619) 
(list 2880.4833 869.3722) 
(list 2880.4833 869.3825) 
(list 2880.4833 869.3928) 
(list 2880.4833 869.4031) 
(list 2880.4833 869.4133) 
(list 2880.4833 869.4236) 
(list 2880.4833 869.4339) 
(list 2880.4833 869.4442) 
(list 2880.4833 869.4544) 
(list 2880.4833 869.4647) 
(list 2880.4833 869.475) 
(list 2880.4833 869.4853) 
(list 2880.4833 869.4956) 
(list 2880.4833 869.5058) 
(list 2880.4833 869.5161) 
(list 2880.4833 869.5264) 
(list 2880.4833 869.5367) 
(list 2880.4833 869.5469) 
(list 2880.4833 869.5572) 
(list 2880.4833 869.5675) 
(list 2880.4833 869.5778) 
(list 2880.4833 869.5881) 
(list 2880.4833 869.5983) 
(list 2880.4833 869.6086) 
(list 2880.4833 869.6189) 
(list 2880.4833 869.6292) 
(list 2880.4833 869.6394) 
(list 2880.4833 869.6497) 
(list 2880.4833 869.66) 
(list 2881.086 869.66)))
(apply 'command (append '("pline") coords '("c")))
(setq tap9 (ssadd (entlast) tap9))
(command "_mirror" (entlast) "" "2880,900" "2880,901" "No")
(setq tap9 (ssadd (entlast) tap9))
(setq coords (list 
(list 2880 869.66) 
(list 2880.135 869.66) 
(list 2880.135 869.6703) 
(list 2880.135 869.6806) 
(list 2880.135 869.6908) 
(list 2880.135 869.7011) 
(list 2880.135 869.7114) 
(list 2880.135 869.7217) 
(list 2880.135 869.7319) 
(list 2880.135 869.7422) 
(list 2880.135 869.7525) 
(list 2880.135 869.7628) 
(list 2880.135 869.7731) 
(list 2880.135 869.7833) 
(list 2880.135 869.7936) 
(list 2880.135 869.8039) 
(list 2880.135 869.8142) 
(list 2880.135 869.8244) 
(list 2880.135 869.8347) 
(list 2880.135 869.845) 
(list 2880.135 869.8553) 
(list 2880.135 869.8656) 
(list 2880.135 869.8758) 
(list 2880.135 869.8861) 
(list 2880.135 869.8964) 
(list 2880.135 869.9067) 
(list 2880.135 869.9169) 
(list 2880.135 869.9272) 
(list 2880.135 869.9375) 
(list 2880.135 869.9478) 
(list 2880.135 869.9581) 
(list 2880.135 869.9683) 
(list 2880.135 869.9786) 
(list 2880.135 869.9889) 
(list 2880.135 869.9992) 
(list 2880.135 870.0094) 
(list 2880.135 870.0197) 
(list 2880.135 870.03) 
(list 2880 870.03)))
(apply 'command (append '("pline") coords '("c")))
(setq tap9 (ssadd (entlast) tap9))
(command "_mirror" (entlast) "" "2880,900" "2880,901" "No")
(setq tap9 (ssadd (entlast) tap9))
(setq coords (list 
(list 2880.4918 869.66) 
(list 2880.4833 869.66) 
(list 2880.4825 869.6703) 
(list 2880.4798 869.6806) 
(list 2880.4752 869.6908) 
(list 2880.4688 869.7011) 
(list 2880.4608 869.7114) 
(list 2880.4515 869.7217) 
(list 2880.4411 869.7319) 
(list 2880.4299 869.7422) 
(list 2880.4183 869.7525) 
(list 2880.4066 869.7628) 
(list 2880.3952 869.7731) 
(list 2880.3844 869.7833) 
(list 2880.3746 869.7936) 
(list 2880.3661 869.8039) 
(list 2880.3591 869.8142) 
(list 2880.3538 869.8244) 
(list 2880.3505 869.8347) 
(list 2880.3493 869.845) 
(list 2880.3501 869.8553) 
(list 2880.353 869.8656) 
(list 2880.358 869.8758) 
(list 2880.3648 869.8861) 
(list 2880.3733 869.8964) 
(list 2880.3832 869.9067) 
(list 2880.3943 869.9169) 
(list 2880.4062 869.9272) 
(list 2880.4185 869.9375) 
(list 2880.4309 869.9478) 
(list 2880.443 869.9581) 
(list 2880.4545 869.9683) 
(list 2880.4649 869.9786) 
(list 2880.4739 869.9889) 
(list 2880.4814 869.9992) 
(list 2880.4869 870.0094) 
(list 2880.4905 870.0197) 
(list 2880.4918 870.03) 
(list 2880.4918 870.03)))
(apply 'command (append '("pline") coords '("c")))
(setq tap9 (ssadd (entlast) tap9))
(command "_mirror" (entlast) "" "2880,900" "2880,901" "No")
(setq tap9 (ssadd (entlast) tap9))
(setq coords (list 
(list 2881.086 869.66) 
(list 2880.4918 869.66) 
(list 2880.4918 869.6703) 
(list 2880.4918 869.6806) 
(list 2880.4918 869.6908) 
(list 2880.4918 869.7011) 
(list 2880.4918 869.7114) 
(list 2880.4918 869.7217) 
(list 2880.4918 869.7319) 
(list 2880.4918 869.7422) 
(list 2880.4918 869.7525) 
(list 2880.4918 869.7628) 
(list 2880.4918 869.7731) 
(list 2880.4918 869.7833) 
(list 2880.4918 869.7936) 
(list 2880.4918 869.8039) 
(list 2880.4918 869.8142) 
(list 2880.4918 869.8244) 
(list 2880.4918 869.8347) 
(list 2880.4918 869.845) 
(list 2880.4918 869.8553) 
(list 2880.4918 869.8656) 
(list 2880.4918 869.8758) 
(list 2880.4918 869.8861) 
(list 2880.4918 869.8964) 
(list 2880.4918 869.9067) 
(list 2880.4918 869.9169) 
(list 2880.4918 869.9272) 
(list 2880.4918 869.9375) 
(list 2880.4918 869.9478) 
(list 2880.4918 869.9581) 
(list 2880.4918 869.9683) 
(list 2880.4918 869.9786) 
(list 2880.4918 869.9889) 
(list 2880.4918 869.9992) 
(list 2880.4918 870.0094) 
(list 2880.4918 870.0197) 
(list 2880.4918 870.03) 
(list 2881.086 870.03)))
(apply 'command (append '("pline") coords '("c")))
(setq tap9 (ssadd (entlast) tap9))
(command "_mirror" (entlast) "" "2880,900" "2880,901" "No")
(setq tap9 (ssadd (entlast) tap9))
(setq coords (list 
(list 2880 870.03) 
(list 2880.135 870.03) 
(list 2880.135 870.0403) 
(list 2880.135 870.0506) 
(list 2880.135 870.0608) 
(list 2880.135 870.0711) 
(list 2880.135 870.0814) 
(list 2880.135 870.0917) 
(list 2880.135 870.1019) 
(list 2880.135 870.1122) 
(list 2880.135 870.1225) 
(list 2880.135 870.1328) 
(list 2880.135 870.1431) 
(list 2880.135 870.1533) 
(list 2880.135 870.1636) 
(list 2880.135 870.1739) 
(list 2880.135 870.1842) 
(list 2880.135 870.1944) 
(list 2880.135 870.2047) 
(list 2880.135 870.215) 
(list 2880.135 870.2253) 
(list 2880.135 870.2356) 
(list 2880.135 870.2458) 
(list 2880.135 870.2561) 
(list 2880.135 870.2664) 
(list 2880.135 870.2767) 
(list 2880.135 870.2869) 
(list 2880.135 870.2972) 
(list 2880.135 870.3075) 
(list 2880.135 870.3178) 
(list 2880.135 870.3281) 
(list 2880.135 870.3383) 
(list 2880.135 870.3486) 
(list 2880.135 870.3589) 
(list 2880.135 870.3692) 
(list 2880.135 870.3794) 
(list 2880.135 870.3897) 
(list 2880.135 870.4) 
(list 2880 870.4)))
(apply 'command (append '("pline") coords '("c")))
(setq tap9 (ssadd (entlast) tap9))
(command "_mirror" (entlast) "" "2880,900" "2880,901" "No")
(setq tap9 (ssadd (entlast) tap9))
(setq coords (list 
(list 2880.5003 870.03) 
(list 2880.4918 870.03) 
(list 2880.4909 870.0403) 
(list 2880.4878 870.0506) 
(list 2880.4826 870.0608) 
(list 2880.4754 870.0711) 
(list 2880.4664 870.0814) 
(list 2880.4559 870.0917) 
(list 2880.4443 870.1019) 
(list 2880.4317 870.1122) 
(list 2880.4187 870.1225) 
(list 2880.4056 870.1328) 
(list 2880.3928 870.1431) 
(list 2880.3808 870.1533) 
(list 2880.3698 870.1636) 
(list 2880.3603 870.1739) 
(list 2880.3524 870.1842) 
(list 2880.3466 870.1944) 
(list 2880.3429 870.2047) 
(list 2880.3415 870.215) 
(list 2880.3425 870.2253) 
(list 2880.3458 870.2356) 
(list 2880.3513 870.2458) 
(list 2880.359 870.2561) 
(list 2880.3685 870.2664) 
(list 2880.3796 870.2767) 
(list 2880.3919 870.2869) 
(list 2880.4052 870.2972) 
(list 2880.4189 870.3075) 
(list 2880.4327 870.3178) 
(list 2880.4462 870.3281) 
(list 2880.4589 870.3383) 
(list 2880.4705 870.3486) 
(list 2880.4806 870.3589) 
(list 2880.4888 870.3692) 
(list 2880.495 870.3794) 
(list 2880.4989 870.3897) 
(list 2880.5003 870.4) 
(list 2880.5003 870.4)))
(apply 'command (append '("pline") coords '("c")))
(setq tap9 (ssadd (entlast) tap9))
(command "_mirror" (entlast) "" "2880,900" "2880,901" "No")
(setq tap9 (ssadd (entlast) tap9))
(setq coords (list 
(list 2881.086 870.03) 
(list 2880.5003 870.03) 
(list 2880.5003 870.0403) 
(list 2880.5003 870.0506) 
(list 2880.5003 870.0608) 
(list 2880.5003 870.0711) 
(list 2880.5003 870.0814) 
(list 2880.5003 870.0917) 
(list 2880.5003 870.1019) 
(list 2880.5003 870.1122) 
(list 2880.5003 870.1225) 
(list 2880.5003 870.1328) 
(list 2880.5003 870.1431) 
(list 2880.5003 870.1533) 
(list 2880.5003 870.1636) 
(list 2880.5003 870.1739) 
(list 2880.5003 870.1842) 
(list 2880.5003 870.1944) 
(list 2880.5003 870.2047) 
(list 2880.5003 870.215) 
(list 2880.5003 870.2253) 
(list 2880.5003 870.2356) 
(list 2880.5003 870.2458) 
(list 2880.5003 870.2561) 
(list 2880.5003 870.2664) 
(list 2880.5003 870.2767) 
(list 2880.5003 870.2869) 
(list 2880.5003 870.2972) 
(list 2880.5003 870.3075) 
(list 2880.5003 870.3178) 
(list 2880.5003 870.3281) 
(list 2880.5003 870.3383) 
(list 2880.5003 870.3486) 
(list 2880.5003 870.3589) 
(list 2880.5003 870.3692) 
(list 2880.5003 870.3794) 
(list 2880.5003 870.3897) 
(list 2880.5003 870.4) 
(list 2881.086 870.4)))
(apply 'command (append '("pline") coords '("c")))
(setq tap9 (ssadd (entlast) tap9))
(command "_mirror" (entlast) "" "2880,900" "2880,901" "No")
(setq tap9 (ssadd (entlast) tap9))
(setq coords (list 
(list 2880 870.4) 
(list 2880.135 870.4) 
(list 2880.135 870.4103) 
(list 2880.135 870.4206) 
(list 2880.135 870.4308) 
(list 2880.135 870.4411) 
(list 2880.135 870.4514) 
(list 2880.135 870.4617) 
(list 2880.135 870.4719) 
(list 2880.135 870.4822) 
(list 2880.135 870.4925) 
(list 2880.135 870.5028) 
(list 2880.135 870.5131) 
(list 2880.135 870.5233) 
(list 2880.135 870.5336) 
(list 2880.135 870.5439) 
(list 2880.135 870.5542) 
(list 2880.135 870.5644) 
(list 2880.135 870.5747) 
(list 2880.135 870.585) 
(list 2880.135 870.5953) 
(list 2880.135 870.6056) 
(list 2880.135 870.6158) 
(list 2880.135 870.6261) 
(list 2880.135 870.6364) 
(list 2880.135 870.6467) 
(list 2880.135 870.6569) 
(list 2880.135 870.6672) 
(list 2880.135 870.6775) 
(list 2880.135 870.6878) 
(list 2880.135 870.6981) 
(list 2880.135 870.7083) 
(list 2880.135 870.7186) 
(list 2880.135 870.7289) 
(list 2880.135 870.7392) 
(list 2880.135 870.7494) 
(list 2880.135 870.7597) 
(list 2880.135 870.77) 
(list 2880 870.77)))
(apply 'command (append '("pline") coords '("c")))
(setq tap9 (ssadd (entlast) tap9))
(command "_mirror" (entlast) "" "2880,900" "2880,901" "No")
(setq tap9 (ssadd (entlast) tap9))
(setq coords (list 
(list 2880.5089 870.4) 
(list 2880.5003 870.4) 
(list 2880.4993 870.4103) 
(list 2880.4959 870.4206) 
(list 2880.4901 870.4308) 
(list 2880.482 870.4411) 
(list 2880.4721 870.4514) 
(list 2880.4604 870.4617) 
(list 2880.4474 870.4719) 
(list 2880.4335 870.4822) 
(list 2880.4191 870.4925) 
(list 2880.4046 870.5028) 
(list 2880.3905 870.5131) 
(list 2880.3771 870.5233) 
(list 2880.365 870.5336) 
(list 2880.3544 870.5439) 
(list 2880.3458 870.5542) 
(list 2880.3394 870.5644) 
(list 2880.3353 870.5747) 
(list 2880.3338 870.585) 
(list 2880.3349 870.5953) 
(list 2880.3385 870.6056) 
(list 2880.3447 870.6158) 
(list 2880.3531 870.6261) 
(list 2880.3636 870.6364) 
(list 2880.3759 870.6467) 
(list 2880.3895 870.6569) 
(list 2880.4041 870.6672) 
(list 2880.4193 870.6775) 
(list 2880.4345 870.6878) 
(list 2880.4494 870.6981) 
(list 2880.4634 870.7083) 
(list 2880.4761 870.7186) 
(list 2880.4872 870.7289) 
(list 2880.4963 870.7392) 
(list 2880.503 870.7494) 
(list 2880.5073 870.7597) 
(list 2880.5089 870.77) 
(list 2880.5089 870.77)))
(apply 'command (append '("pline") coords '("c")))
(setq tap9 (ssadd (entlast) tap9))
(command "_mirror" (entlast) "" "2880,900" "2880,901" "No")
(setq tap9 (ssadd (entlast) tap9))
(setq coords (list 
(list 2881.086 870.4) 
(list 2880.5089 870.4) 
(list 2880.5089 870.4103) 
(list 2880.5089 870.4206) 
(list 2880.5089 870.4308) 
(list 2880.5089 870.4411) 
(list 2880.5089 870.4514) 
(list 2880.5089 870.4617) 
(list 2880.5089 870.4719) 
(list 2880.5089 870.4822) 
(list 2880.5089 870.4925) 
(list 2880.5089 870.5028) 
(list 2880.5089 870.5131) 
(list 2880.5089 870.5233) 
(list 2880.5089 870.5336) 
(list 2880.5089 870.5439) 
(list 2880.5089 870.5542) 
(list 2880.5089 870.5644) 
(list 2880.5089 870.5747) 
(list 2880.5089 870.585) 
(list 2880.5089 870.5953) 
(list 2880.5089 870.6056) 
(list 2880.5089 870.6158) 
(list 2880.5089 870.6261) 
(list 2880.5089 870.6364) 
(list 2880.5089 870.6467) 
(list 2880.5089 870.6569) 
(list 2880.5089 870.6672) 
(list 2880.5089 870.6775) 
(list 2880.5089 870.6878) 
(list 2880.5089 870.6981) 
(list 2880.5089 870.7083) 
(list 2880.5089 870.7186) 
(list 2880.5089 870.7289) 
(list 2880.5089 870.7392) 
(list 2880.5089 870.7494) 
(list 2880.5089 870.7597) 
(list 2880.5089 870.77) 
(list 2881.086 870.77)))
(apply 'command (append '("pline") coords '("c")))
(setq tap9 (ssadd (entlast) tap9))
(command "_mirror" (entlast) "" "2880,900" "2880,901" "No")
(setq tap9 (ssadd (entlast) tap9))
(setq coords (list 
(list 2880 870.77) 
(list 2880.135 870.77) 
(list 2880.135 870.7803) 
(list 2880.135 870.7906) 
(list 2880.135 870.8008) 
(list 2880.135 870.8111) 
(list 2880.135 870.8214) 
(list 2880.135 870.8317) 
(list 2880.135 870.8419) 
(list 2880.135 870.8522) 
(list 2880.135 870.8625) 
(list 2880.135 870.8728) 
(list 2880.135 870.8831) 
(list 2880.135 870.8933) 
(list 2880.135 870.9036) 
(list 2880.135 870.9139) 
(list 2880.135 870.9242) 
(list 2880.135 870.9344) 
(list 2880.135 870.9447) 
(list 2880.135 870.955) 
(list 2880.135 870.9653) 
(list 2880.135 870.9756) 
(list 2880.135 870.9858) 
(list 2880.135 870.9961) 
(list 2880.135 871.0064) 
(list 2880.135 871.0167) 
(list 2880.135 871.0269) 
(list 2880.135 871.0372) 
(list 2880.135 871.0475) 
(list 2880.135 871.0578) 
(list 2880.135 871.0681) 
(list 2880.135 871.0783) 
(list 2880.135 871.0886) 
(list 2880.135 871.0989) 
(list 2880.135 871.1092) 
(list 2880.135 871.1194) 
(list 2880.135 871.1297) 
(list 2880.135 871.14) 
(list 2880 871.14)))
(apply 'command (append '("pline") coords '("c")))
(setq tap9 (ssadd (entlast) tap9))
(command "_mirror" (entlast) "" "2880,900" "2880,901" "No")
(setq tap9 (ssadd (entlast) tap9))
(setq coords (list 
(list 2880.5174 870.77) 
(list 2880.5089 870.77) 
(list 2880.5077 870.7803) 
(list 2880.5039 870.7906) 
(list 2880.4975 870.8008) 
(list 2880.4887 870.8111) 
(list 2880.4777 870.8214) 
(list 2880.4649 870.8317) 
(list 2880.4506 870.8419) 
(list 2880.4353 870.8522) 
(list 2880.4195 870.8625) 
(list 2880.4036 870.8728) 
(list 2880.3881 870.8831) 
(list 2880.3734 870.8933) 
(list 2880.3601 870.9036) 
(list 2880.3486 870.9139) 
(list 2880.3392 870.9242) 
(list 2880.3321 870.9344) 
(list 2880.3277 870.9447) 
(list 2880.3261 870.955) 
(list 2880.3273 870.9653) 
(list 2880.3313 870.9756) 
(list 2880.338 870.9858) 
(list 2880.3473 870.9961) 
(list 2880.3588 871.0064) 
(list 2880.3722 871.0167) 
(list 2880.3871 871.0269) 
(list 2880.4031 871.0372) 
(list 2880.4197 871.0475) 
(list 2880.4363 871.0578) 
(list 2880.4526 871.0681) 
(list 2880.4679 871.0783) 
(list 2880.4818 871.0886) 
(list 2880.4938 871.0989) 
(list 2880.5037 871.1092) 
(list 2880.5111 871.1194) 
(list 2880.5157 871.1297) 
(list 2880.5174 871.14) 
(list 2880.5174 871.14)))
(apply 'command (append '("pline") coords '("c")))
(setq tap9 (ssadd (entlast) tap9))
(command "_mirror" (entlast) "" "2880,900" "2880,901" "No")
(setq tap9 (ssadd (entlast) tap9))
(setq coords (list 
(list 2881.086 870.77) 
(list 2880.5174 870.77) 
(list 2880.5174 870.7803) 
(list 2880.5174 870.7906) 
(list 2880.5174 870.8008) 
(list 2880.5174 870.8111) 
(list 2880.5174 870.8214) 
(list 2880.5174 870.8317) 
(list 2880.5174 870.8419) 
(list 2880.5174 870.8522) 
(list 2880.5174 870.8625) 
(list 2880.5174 870.8728) 
(list 2880.5174 870.8831) 
(list 2880.5174 870.8933) 
(list 2880.5174 870.9036) 
(list 2880.5174 870.9139) 
(list 2880.5174 870.9242) 
(list 2880.5174 870.9344) 
(list 2880.5174 870.9447) 
(list 2880.5174 870.955) 
(list 2880.5174 870.9653) 
(list 2880.5174 870.9756) 
(list 2880.5174 870.9858) 
(list 2880.5174 870.9961) 
(list 2880.5174 871.0064) 
(list 2880.5174 871.0167) 
(list 2880.5174 871.0269) 
(list 2880.5174 871.0372) 
(list 2880.5174 871.0475) 
(list 2880.5174 871.0578) 
(list 2880.5174 871.0681) 
(list 2880.5174 871.0783) 
(list 2880.5174 871.0886) 
(list 2880.5174 871.0989) 
(list 2880.5174 871.1092) 
(list 2880.5174 871.1194) 
(list 2880.5174 871.1297) 
(list 2880.5174 871.14) 
(list 2881.086 871.14)))
(apply 'command (append '("pline") coords '("c")))
(setq tap9 (ssadd (entlast) tap9))
(command "_mirror" (entlast) "" "2880,900" "2880,901" "No")
(setq tap9 (ssadd (entlast) tap9))
(setq coords (list 
(list 2880 871.14) 
(list 2880.135 871.14) 
(list 2880.135 871.1503) 
(list 2880.135 871.1606) 
(list 2880.135 871.1708) 
(list 2880.135 871.1811) 
(list 2880.135 871.1914) 
(list 2880.135 871.2017) 
(list 2880.135 871.2119) 
(list 2880.135 871.2222) 
(list 2880.135 871.2325) 
(list 2880.135 871.2428) 
(list 2880.135 871.2531) 
(list 2880.135 871.2633) 
(list 2880.135 871.2736) 
(list 2880.135 871.2839) 
(list 2880.135 871.2942) 
(list 2880.135 871.3044) 
(list 2880.135 871.3147) 
(list 2880.135 871.325) 
(list 2880.135 871.3353) 
(list 2880.135 871.3456) 
(list 2880.135 871.3558) 
(list 2880.135 871.3661) 
(list 2880.135 871.3764) 
(list 2880.135 871.3867) 
(list 2880.135 871.3969) 
(list 2880.135 871.4072) 
(list 2880.135 871.4175) 
(list 2880.135 871.4278) 
(list 2880.135 871.4381) 
(list 2880.135 871.4483) 
(list 2880.135 871.4586) 
(list 2880.135 871.4689) 
(list 2880.135 871.4792) 
(list 2880.135 871.4894) 
(list 2880.135 871.4997) 
(list 2880.135 871.51) 
(list 2880 871.51)))
(apply 'command (append '("pline") coords '("c")))
(setq tap9 (ssadd (entlast) tap9))
(command "_mirror" (entlast) "" "2880,900" "2880,901" "No")
(setq tap9 (ssadd (entlast) tap9))
(setq coords (list 
(list 2880.5259 871.14) 
(list 2880.5174 871.14) 
(list 2880.5161 871.1503) 
(list 2880.512 871.1606) 
(list 2880.5049 871.1708) 
(list 2880.4953 871.1811) 
(list 2880.4833 871.1914) 
(list 2880.4693 871.2017) 
(list 2880.4538 871.2119) 
(list 2880.4372 871.2222) 
(list 2880.4199 871.2325) 
(list 2880.4026 871.2428) 
(list 2880.3857 871.2531) 
(list 2880.3698 871.2633) 
(list 2880.3553 871.2736) 
(list 2880.3428 871.2839) 
(list 2880.3325 871.2942) 
(list 2880.3249 871.3044) 
(list 2880.3201 871.3147) 
(list 2880.3183 871.325) 
(list 2880.3197 871.3353) 
(list 2880.3241 871.3456) 
(list 2880.3314 871.3558) 
(list 2880.3415 871.3661) 
(list 2880.354 871.3764) 
(list 2880.3686 871.3867) 
(list 2880.3848 871.3969) 
(list 2880.4021 871.4072) 
(list 2880.4201 871.4175) 
(list 2880.4382 871.4278) 
(list 2880.4557 871.4381) 
(list 2880.4723 871.4483) 
(list 2880.4874 871.4586) 
(list 2880.5005 871.4689) 
(list 2880.5111 871.4792) 
(list 2880.5191 871.4894) 
(list 2880.5241 871.4997) 
(list 2880.5259 871.51) 
(list 2880.5259 871.51)))
(apply 'command (append '("pline") coords '("c")))
(setq tap9 (ssadd (entlast) tap9))
(command "_mirror" (entlast) "" "2880,900" "2880,901" "No")
(setq tap9 (ssadd (entlast) tap9))
(setq coords (list 
(list 2881.086 871.14) 
(list 2880.5259 871.14) 
(list 2880.5259 871.1503) 
(list 2880.5259 871.1606) 
(list 2880.5259 871.1708) 
(list 2880.5259 871.1811) 
(list 2880.5259 871.1914) 
(list 2880.5259 871.2017) 
(list 2880.5259 871.2119) 
(list 2880.5259 871.2222) 
(list 2880.5259 871.2325) 
(list 2880.5259 871.2428) 
(list 2880.5259 871.2531) 
(list 2880.5259 871.2633) 
(list 2880.5259 871.2736) 
(list 2880.5259 871.2839) 
(list 2880.5259 871.2942) 
(list 2880.5259 871.3044) 
(list 2880.5259 871.3147) 
(list 2880.5259 871.325) 
(list 2880.5259 871.3353) 
(list 2880.5259 871.3456) 
(list 2880.5259 871.3558) 
(list 2880.5259 871.3661) 
(list 2880.5259 871.3764) 
(list 2880.5259 871.3867) 
(list 2880.5259 871.3969) 
(list 2880.5259 871.4072) 
(list 2880.5259 871.4175) 
(list 2880.5259 871.4278) 
(list 2880.5259 871.4381) 
(list 2880.5259 871.4483) 
(list 2880.5259 871.4586) 
(list 2880.5259 871.4689) 
(list 2880.5259 871.4792) 
(list 2880.5259 871.4894) 
(list 2880.5259 871.4997) 
(list 2880.5259 871.51) 
(list 2881.086 871.51)))
(apply 'command (append '("pline") coords '("c")))
(setq tap9 (ssadd (entlast) tap9))
(command "_mirror" (entlast) "" "2880,900" "2880,901" "No")
(setq tap9 (ssadd (entlast) tap9))
(setq coords (list 
(list 2880 871.51) 
(list 2880.135 871.51) 
(list 2880.135 871.5203) 
(list 2880.135 871.5306) 
(list 2880.135 871.5408) 
(list 2880.135 871.5511) 
(list 2880.135 871.5614) 
(list 2880.135 871.5717) 
(list 2880.135 871.5819) 
(list 2880.135 871.5922) 
(list 2880.135 871.6025) 
(list 2880.135 871.6128) 
(list 2880.135 871.6231) 
(list 2880.135 871.6333) 
(list 2880.135 871.6436) 
(list 2880.135 871.6539) 
(list 2880.135 871.6642) 
(list 2880.135 871.6744) 
(list 2880.135 871.6847) 
(list 2880.135 871.695) 
(list 2880.135 871.7053) 
(list 2880.135 871.7156) 
(list 2880.135 871.7258) 
(list 2880.135 871.7361) 
(list 2880.135 871.7464) 
(list 2880.135 871.7567) 
(list 2880.135 871.7669) 
(list 2880.135 871.7772) 
(list 2880.135 871.7875) 
(list 2880.135 871.7978) 
(list 2880.135 871.8081) 
(list 2880.135 871.8183) 
(list 2880.135 871.8286) 
(list 2880.135 871.8389) 
(list 2880.135 871.8492) 
(list 2880.135 871.8594) 
(list 2880.135 871.8697) 
(list 2880.135 871.88) 
(list 2880 871.88)))
(apply 'command (append '("pline") coords '("c")))
(setq tap9 (ssadd (entlast) tap9))
(command "_mirror" (entlast) "" "2880,900" "2880,901" "No")
(setq tap9 (ssadd (entlast) tap9))
(setq coords (list 
(list 2880.5345 871.51) 
(list 2880.5259 871.51) 
(list 2880.5246 871.5203) 
(list 2880.52 871.5306) 
(list 2880.5124 871.5408) 
(list 2880.5019 871.5511) 
(list 2880.4889 871.5614) 
(list 2880.4738 871.5717) 
(list 2880.457 871.5819) 
(list 2880.439 871.5922) 
(list 2880.4203 871.6025) 
(list 2880.4016 871.6128) 
(list 2880.3833 871.6231) 
(list 2880.3661 871.6333) 
(list 2880.3505 871.6436) 
(list 2880.3369 871.6539) 
(list 2880.3259 871.6642) 
(list 2880.3176 871.6744) 
(list 2880.3125 871.6847) 
(list 2880.3106 871.695) 
(list 2880.3121 871.7053) 
(list 2880.3168 871.7156) 
(list 2880.3248 871.7258) 
(list 2880.3356 871.7361) 
(list 2880.3492 871.7464) 
(list 2880.3649 871.7567) 
(list 2880.3824 871.7669) 
(list 2880.4011 871.7772) 
(list 2880.4205 871.7875) 
(list 2880.44 871.7978) 
(list 2880.4589 871.8081) 
(list 2880.4768 871.8183) 
(list 2880.493 871.8286) 
(list 2880.5071 871.8389) 
(list 2880.5186 871.8492) 
(list 2880.5272 871.8594) 
(list 2880.5325 871.8697) 
(list 2880.5345 871.88) 
(list 2880.5345 871.88)))
(apply 'command (append '("pline") coords '("c")))
(setq tap9 (ssadd (entlast) tap9))
(command "_mirror" (entlast) "" "2880,900" "2880,901" "No")
(setq tap9 (ssadd (entlast) tap9))
(setq coords (list 
(list 2881.086 871.51) 
(list 2880.5345 871.51) 
(list 2880.5345 871.5203) 
(list 2880.5345 871.5306) 
(list 2880.5345 871.5408) 
(list 2880.5345 871.5511) 
(list 2880.5345 871.5614) 
(list 2880.5345 871.5717) 
(list 2880.5345 871.5819) 
(list 2880.5345 871.5922) 
(list 2880.5345 871.6025) 
(list 2880.5345 871.6128) 
(list 2880.5345 871.6231) 
(list 2880.5345 871.6333) 
(list 2880.5345 871.6436) 
(list 2880.5345 871.6539) 
(list 2880.5345 871.6642) 
(list 2880.5345 871.6744) 
(list 2880.5345 871.6847) 
(list 2880.5345 871.695) 
(list 2880.5345 871.7053) 
(list 2880.5345 871.7156) 
(list 2880.5345 871.7258) 
(list 2880.5345 871.7361) 
(list 2880.5345 871.7464) 
(list 2880.5345 871.7567) 
(list 2880.5345 871.7669) 
(list 2880.5345 871.7772) 
(list 2880.5345 871.7875) 
(list 2880.5345 871.7978) 
(list 2880.5345 871.8081) 
(list 2880.5345 871.8183) 
(list 2880.5345 871.8286) 
(list 2880.5345 871.8389) 
(list 2880.5345 871.8492) 
(list 2880.5345 871.8594) 
(list 2880.5345 871.8697) 
(list 2880.5345 871.88) 
(list 2881.086 871.88)))
(apply 'command (append '("pline") coords '("c")))
(setq tap9 (ssadd (entlast) tap9))
(command "_mirror" (entlast) "" "2880,900" "2880,901" "No")
(setq tap9 (ssadd (entlast) tap9))
(setq coords (list 
(list 2880 871.88) 
(list 2880.135 871.88) 
(list 2880.135 871.8903) 
(list 2880.135 871.9006) 
(list 2880.135 871.9108) 
(list 2880.135 871.9211) 
(list 2880.135 871.9314) 
(list 2880.135 871.9417) 
(list 2880.135 871.9519) 
(list 2880.135 871.9622) 
(list 2880.135 871.9725) 
(list 2880.135 871.9828) 
(list 2880.135 871.9931) 
(list 2880.135 872.0033) 
(list 2880.135 872.0136) 
(list 2880.135 872.0239) 
(list 2880.135 872.0342) 
(list 2880.135 872.0444) 
(list 2880.135 872.0547) 
(list 2880.135 872.065) 
(list 2880.135 872.0753) 
(list 2880.135 872.0856) 
(list 2880.135 872.0958) 
(list 2880.135 872.1061) 
(list 2880.135 872.1164) 
(list 2880.135 872.1267) 
(list 2880.135 872.1369) 
(list 2880.135 872.1472) 
(list 2880.135 872.1575) 
(list 2880.135 872.1678) 
(list 2880.135 872.1781) 
(list 2880.135 872.1883) 
(list 2880.135 872.1986) 
(list 2880.135 872.2089) 
(list 2880.135 872.2192) 
(list 2880.135 872.2294) 
(list 2880.135 872.2397) 
(list 2880.135 872.25) 
(list 2880 872.25)))
(apply 'command (append '("pline") coords '("c")))
(setq tap9 (ssadd (entlast) tap9))
(command "_mirror" (entlast) "" "2880,900" "2880,901" "No")
(setq tap9 (ssadd (entlast) tap9))
(setq coords (list 
(list 2880.543 871.88) 
(list 2880.5345 871.88) 
(list 2880.533 871.8903) 
(list 2880.528 871.9006) 
(list 2880.5198 871.9108) 
(list 2880.5086 871.9211) 
(list 2880.4946 871.9314) 
(list 2880.4783 871.9417) 
(list 2880.4602 871.9519) 
(list 2880.4408 871.9622) 
(list 2880.4207 871.9725) 
(list 2880.4005 871.9828) 
(list 2880.3809 871.9931) 
(list 2880.3624 872.0033) 
(list 2880.3457 872.0136) 
(list 2880.3311 872.0239) 
(list 2880.3192 872.0342) 
(list 2880.3104 872.0444) 
(list 2880.3049 872.0547) 
(list 2880.3029 872.065) 
(list 2880.3044 872.0753) 
(list 2880.3096 872.0856) 
(list 2880.3181 872.0958) 
(list 2880.3298 872.1061) 
(list 2880.3443 872.1164) 
(list 2880.3612 872.1267) 
(list 2880.38 872.1369) 
(list 2880.4001 872.1472) 
(list 2880.4209 872.1575) 
(list 2880.4418 872.1678) 
(list 2880.4621 872.1781) 
(list 2880.4813 872.1883) 
(list 2880.4986 872.1986) 
(list 2880.5137 872.2089) 
(list 2880.526 872.2192) 
(list 2880.5352 872.2294) 
(list 2880.5409 872.2397) 
(list 2880.543 872.25) 
(list 2880.543 872.25)))
(apply 'command (append '("pline") coords '("c")))
(setq tap9 (ssadd (entlast) tap9))
(command "_mirror" (entlast) "" "2880,900" "2880,901" "No")
(setq tap9 (ssadd (entlast) tap9))
(setq coords (list 
(list 2881.086 871.88) 
(list 2880.543 871.88) 
(list 2880.543 871.8903) 
(list 2880.543 871.9006) 
(list 2880.543 871.9108) 
(list 2880.543 871.9211) 
(list 2880.543 871.9314) 
(list 2880.543 871.9417) 
(list 2880.543 871.9519) 
(list 2880.543 871.9622) 
(list 2880.543 871.9725) 
(list 2880.543 871.9828) 
(list 2880.543 871.9931) 
(list 2880.543 872.0033) 
(list 2880.543 872.0136) 
(list 2880.543 872.0239) 
(list 2880.543 872.0342) 
(list 2880.543 872.0444) 
(list 2880.543 872.0547) 
(list 2880.543 872.065) 
(list 2880.543 872.0753) 
(list 2880.543 872.0856) 
(list 2880.543 872.0958) 
(list 2880.543 872.1061) 
(list 2880.543 872.1164) 
(list 2880.543 872.1267) 
(list 2880.543 872.1369) 
(list 2880.543 872.1472) 
(list 2880.543 872.1575) 
(list 2880.543 872.1678) 
(list 2880.543 872.1781) 
(list 2880.543 872.1883) 
(list 2880.543 872.1986) 
(list 2880.543 872.2089) 
(list 2880.543 872.2192) 
(list 2880.543 872.2294) 
(list 2880.543 872.2397) 
(list 2880.543 872.25) 
(list 2881.086 872.25)))
(apply 'command (append '("pline") coords '("c")))
(setq tap9 (ssadd (entlast) tap9))
(command "_mirror" (entlast) "" "2880,900" "2880,901" "No")
(setq tap9 (ssadd (entlast) tap9))
(command "_block" "blktap9" "2880,900" tap9 "")
(command "_insert" "blktap9" "2880,900" "1" "1" "0")
(command "_insert" "blktap9" "2880,900" "1" "1" "180")
(setq uc9 nil)
(setq uc9 (ssadd))
(setq coords (list 
(list 0 -0.185) 
(list 0.135 -0.185) 
(list 0.135 -0.17472) 
(list 0.135 -0.16444) 
(list 0.135 -0.15417) 
(list 0.135 -0.14389) 
(list 0.135 -0.13361) 
(list 0.135 -0.12333) 
(list 0.135 -0.11306) 
(list 0.135 -0.10278) 
(list 0.135 -0.0925) 
(list 0.135 -0.082222) 
(list 0.135 -0.071944) 
(list 0.135 -0.061667) 
(list 0.135 -0.051389) 
(list 0.135 -0.041111) 
(list 0.135 -0.030833) 
(list 0.135 -0.020556) 
(list 0.135 -0.010278) 
(list 0.135 0) 
(list 0.135 0.010278) 
(list 0.135 0.020556) 
(list 0.135 0.030833) 
(list 0.135 0.041111) 
(list 0.135 0.051389) 
(list 0.135 0.061667) 
(list 0.135 0.071944) 
(list 0.135 0.082222) 
(list 0.135 0.0925) 
(list 0.135 0.10278) 
(list 0.135 0.11306) 
(list 0.135 0.12333) 
(list 0.135 0.13361) 
(list 0.135 0.14389) 
(list 0.135 0.15417) 
(list 0.135 0.16444) 
(list 0.135 0.17472) 
(list 0.135 0.185) 
(list 0 0.185)))
(apply 'command (append '("pline") coords '("c")))
(setq uc9 (ssadd (entlast) uc9))
(setq coords (list 
(list 1.086 -0.185) 
(list 0.543 -0.185) 
(list 0.54115 -0.17472) 
(list 0.53564 -0.16444) 
(list 0.52665 -0.15417) 
(list 0.51446 -0.14389) 
(list 0.49942 -0.13361) 
(list 0.482 -0.12333) 
(list 0.46273 -0.11306) 
(list 0.44218 -0.10278) 
(list 0.421 -0.0925) 
(list 0.39981 -0.082222) 
(list 0.37927 -0.071944) 
(list 0.36 -0.061667) 
(list 0.34258 -0.051389) 
(list 0.32754 -0.041111) 
(list 0.31534 -0.030833) 
(list 0.30636 -0.020556) 
(list 0.30085 -0.010278) 
(list 0.299 0) 
(list 0.30085 0.010278) 
(list 0.30636 0.020556) 
(list 0.31534 0.030833) 
(list 0.32754 0.041111) 
(list 0.34258 0.051389) 
(list 0.36 0.061667) 
(list 0.37927 0.071944) 
(list 0.39981 0.082222) 
(list 0.421 0.0925) 
(list 0.44218 0.10278) 
(list 0.46273 0.11306) 
(list 0.482 0.12333) 
(list 0.49942 0.13361) 
(list 0.51446 0.14389) 
(list 0.52665 0.15417) 
(list 0.53564 0.16444) 
(list 0.54115 0.17472) 
(list 0.543 0.185) 
(list 1.086 0.185)))
(apply 'command (append '("pline") coords '("c")))
(setq uc9 (ssadd (entlast) uc9))
(command "_block" "blkuc9" "0,0.185" uc9 "")
(command "_insert" "blkuc9" "2880,872.62" "1" "1" "0")
(command "_insert" "blkuc9" "2880,872.25" "1" "1" "180")
(command "_insert" "blkuc9" "2880,872.99" "1" "1" "0")
(command "_insert" "blkuc9" "2880,872.62" "1" "1" "180")
(command "_insert" "blkuc9" "2880,873.36" "1" "1" "0")
(command "_insert" "blkuc9" "2880,872.99" "1" "1" "180")
(command "_insert" "blkuc9" "2880,873.73" "1" "1" "0")
(command "_insert" "blkuc9" "2880,873.36" "1" "1" "180")
(command "_insert" "blkuc9" "2880,874.1" "1" "1" "0")
(command "_insert" "blkuc9" "2880,873.73" "1" "1" "180")
(command "_insert" "blkuc9" "2880,874.47" "1" "1" "0")
(command "_insert" "blkuc9" "2880,874.1" "1" "1" "180")
(command "_insert" "blkuc9" "2880,874.84" "1" "1" "0")
(command "_insert" "blkuc9" "2880,874.47" "1" "1" "180")
(command "_insert" "blkuc9" "2880,875.21" "1" "1" "0")
(command "_insert" "blkuc9" "2880,874.84" "1" "1" "180")
(command "_insert" "blkuc9" "2880,875.58" "1" "1" "0")
(command "_insert" "blkuc9" "2880,875.21" "1" "1" "180")
(command "_insert" "blkuc9" "2880,875.95" "1" "1" "0")
(command "_insert" "blkuc9" "2880,875.58" "1" "1" "180")
(command "_insert" "blkuc9" "2880,876.32" "1" "1" "0")
(command "_insert" "blkuc9" "2880,875.95" "1" "1" "180")
(command "_insert" "blkuc9" "2880,876.69" "1" "1" "0")
(command "_insert" "blkuc9" "2880,876.32" "1" "1" "180")
(command "_insert" "blkuc9" "2880,877.06" "1" "1" "0")
(command "_insert" "blkuc9" "2880,876.69" "1" "1" "180")
(command "_insert" "blkuc9" "2880,877.43" "1" "1" "0")
(command "_insert" "blkuc9" "2880,877.06" "1" "1" "180")
(command "_insert" "blkuc9" "2880,877.8" "1" "1" "0")
(command "_insert" "blkuc9" "2880,877.43" "1" "1" "180")
(command "_insert" "blkuc9" "2880,878.17" "1" "1" "0")
(command "_insert" "blkuc9" "2880,877.8" "1" "1" "180")
(command "_insert" "blkuc9" "2880,878.54" "1" "1" "0")
(command "_insert" "blkuc9" "2880,878.17" "1" "1" "180")
(command "_insert" "blkuc9" "2880,878.91" "1" "1" "0")
(command "_insert" "blkuc9" "2880,878.54" "1" "1" "180")
(command "_insert" "blkuc9" "2880,879.28" "1" "1" "0")
(command "_insert" "blkuc9" "2880,878.91" "1" "1" "180")
(command "_insert" "blkuc9" "2880,879.65" "1" "1" "0")
(command "_insert" "blkuc9" "2880,879.28" "1" "1" "180")
(command "_insert" "blkuc9" "2880,880.02" "1" "1" "0")
(command "_insert" "blkuc9" "2880,879.65" "1" "1" "180")
(command "_insert" "blkuc9" "2880,880.39" "1" "1" "0")
(command "_insert" "blkuc9" "2880,880.02" "1" "1" "180")
(command "_insert" "blkuc9" "2880,880.76" "1" "1" "0")
(command "_insert" "blkuc9" "2880,880.39" "1" "1" "180")
(command "_insert" "blkuc9" "2880,881.13" "1" "1" "0")
(command "_insert" "blkuc9" "2880,880.76" "1" "1" "180")
(command "_insert" "blkuc9" "2880,881.5" "1" "1" "0")
(command "_insert" "blkuc9" "2880,881.13" "1" "1" "180")
(command "_insert" "blkuc9" "2880,881.87" "1" "1" "0")
(command "_insert" "blkuc9" "2880,881.5" "1" "1" "180")
(command "_insert" "blkuc9" "2880,882.24" "1" "1" "0")
(command "_insert" "blkuc9" "2880,881.87" "1" "1" "180")
(command "_insert" "blkuc9" "2880,882.61" "1" "1" "0")
(command "_insert" "blkuc9" "2880,882.24" "1" "1" "180")
(command "_insert" "blkuc9" "2880,882.98" "1" "1" "0")
(command "_insert" "blkuc9" "2880,882.61" "1" "1" "180")
(command "_insert" "blkuc9" "2880,883.35" "1" "1" "0")
(command "_insert" "blkuc9" "2880,882.98" "1" "1" "180")
(command "_insert" "blkuc9" "2880,883.72" "1" "1" "0")
(command "_insert" "blkuc9" "2880,883.35" "1" "1" "180")
(command "_insert" "blkuc9" "2880,884.09" "1" "1" "0")
(command "_insert" "blkuc9" "2880,883.72" "1" "1" "180")
(command "_insert" "blkuc9" "2880,884.46" "1" "1" "0")
(command "_insert" "blkuc9" "2880,884.09" "1" "1" "180")
(command "_insert" "blkuc9" "2880,884.83" "1" "1" "0")
(command "_insert" "blkuc9" "2880,884.46" "1" "1" "180")
(command "_insert" "blkuc9" "2880,885.2" "1" "1" "0")
(command "_insert" "blkuc9" "2880,884.83" "1" "1" "180")
(command "_insert" "blkuc9" "2880,885.57" "1" "1" "0")
(command "_insert" "blkuc9" "2880,885.2" "1" "1" "180")
(command "_insert" "blkuc9" "2880,885.94" "1" "1" "0")
(command "_insert" "blkuc9" "2880,885.57" "1" "1" "180")
(command "_insert" "blkuc9" "2880,886.31" "1" "1" "0")
(command "_insert" "blkuc9" "2880,885.94" "1" "1" "180")
(command "_insert" "blkuc9" "2880,886.68" "1" "1" "0")
(command "_insert" "blkuc9" "2880,886.31" "1" "1" "180")
(command "_insert" "blkuc9" "2880,887.05" "1" "1" "0")
(command "_insert" "blkuc9" "2880,886.68" "1" "1" "180")
(command "_insert" "blkuc9" "2880,887.42" "1" "1" "0")
(command "_insert" "blkuc9" "2880,887.05" "1" "1" "180")
(command "_insert" "blkuc9" "2880,887.79" "1" "1" "0")
(command "_insert" "blkuc9" "2880,887.42" "1" "1" "180")
(command "_insert" "blkuc9" "2880,888.16" "1" "1" "0")
(command "_insert" "blkuc9" "2880,887.79" "1" "1" "180")
(command "_insert" "blkuc9" "2880,888.53" "1" "1" "0")
(command "_insert" "blkuc9" "2880,888.16" "1" "1" "180")
(command "_insert" "blkuc9" "2880,888.9" "1" "1" "0")
(command "_insert" "blkuc9" "2880,888.53" "1" "1" "180")
(command "_insert" "blkuc9" "2880,889.27" "1" "1" "0")
(command "_insert" "blkuc9" "2880,888.9" "1" "1" "180")
(command "_insert" "blkuc9" "2880,889.64" "1" "1" "0")
(command "_insert" "blkuc9" "2880,889.27" "1" "1" "180")
(command "_insert" "blkuc9" "2880,890.01" "1" "1" "0")
(command "_insert" "blkuc9" "2880,889.64" "1" "1" "180")
(command "_insert" "blkuc9" "2880,890.38" "1" "1" "0")
(command "_insert" "blkuc9" "2880,890.01" "1" "1" "180")
(command "_insert" "blkuc9" "2880,890.75" "1" "1" "0")
(command "_insert" "blkuc9" "2880,890.38" "1" "1" "180")
(command "_insert" "blkuc9" "2880,891.12" "1" "1" "0")
(command "_insert" "blkuc9" "2880,890.75" "1" "1" "180")
(command "_insert" "blkuc9" "2880,891.49" "1" "1" "0")
(command "_insert" "blkuc9" "2880,891.12" "1" "1" "180")
(command "_insert" "blkuc9" "2880,891.86" "1" "1" "0")
(command "_insert" "blkuc9" "2880,891.49" "1" "1" "180")
(command "_insert" "blkuc9" "2880,892.23" "1" "1" "0")
(command "_insert" "blkuc9" "2880,891.86" "1" "1" "180")
(command "_insert" "blkuc9" "2880,892.6" "1" "1" "0")
(command "_insert" "blkuc9" "2880,892.23" "1" "1" "180")
(command "_insert" "blkuc9" "2880,892.97" "1" "1" "0")
(command "_insert" "blkuc9" "2880,892.6" "1" "1" "180")
(command "_insert" "blkuc9" "2880,893.34" "1" "1" "0")
(command "_insert" "blkuc9" "2880,892.97" "1" "1" "180")
(command "_insert" "blkuc9" "2880,893.71" "1" "1" "0")
(command "_insert" "blkuc9" "2880,893.34" "1" "1" "180")
(command "_insert" "blkuc9" "2880,894.08" "1" "1" "0")
(command "_insert" "blkuc9" "2880,893.71" "1" "1" "180")
(command "_insert" "blkuc9" "2880,894.45" "1" "1" "0")
(command "_insert" "blkuc9" "2880,894.08" "1" "1" "180")
(command "_insert" "blkuc9" "2880,894.82" "1" "1" "0")
(command "_insert" "blkuc9" "2880,894.45" "1" "1" "180")
(command "_insert" "blkuc9" "2880,895.19" "1" "1" "0")
(command "_insert" "blkuc9" "2880,894.82" "1" "1" "180")
(command "_insert" "blkuc9" "2880,895.56" "1" "1" "0")
(command "_insert" "blkuc9" "2880,895.19" "1" "1" "180")
(command "_insert" "blkuc9" "2880,895.93" "1" "1" "0")
(command "_insert" "blkuc9" "2880,895.56" "1" "1" "180")
(command "_insert" "blkuc9" "2880,896.3" "1" "1" "0")
(command "_insert" "blkuc9" "2880,895.93" "1" "1" "180")
(command "_insert" "blkuc9" "2880,896.67" "1" "1" "0")
(command "_insert" "blkuc9" "2880,896.3" "1" "1" "180")
(command "_insert" "blkuc9" "2880,897.04" "1" "1" "0")
(command "_insert" "blkuc9" "2880,896.67" "1" "1" "180")
(command "_insert" "blkuc9" "2880,897.41" "1" "1" "0")
(command "_insert" "blkuc9" "2880,897.04" "1" "1" "180")
(command "_insert" "blkuc9" "2880,897.78" "1" "1" "0")
(command "_insert" "blkuc9" "2880,897.41" "1" "1" "180")
(command "_insert" "blkuc9" "2880,898.15" "1" "1" "0")
(command "_insert" "blkuc9" "2880,897.78" "1" "1" "180")
(command "_insert" "blkuc9" "2880,898.52" "1" "1" "0")
(command "_insert" "blkuc9" "2880,898.15" "1" "1" "180")
(command "_insert" "blkuc9" "2880,898.89" "1" "1" "0")
(command "_insert" "blkuc9" "2880,898.52" "1" "1" "180")
(command "_insert" "blkuc9" "2880,899.26" "1" "1" "0")
(command "_insert" "blkuc9" "2880,898.89" "1" "1" "180")
(command "_insert" "blkuc9" "2880,899.63" "1" "1" "0")
(command "_insert" "blkuc9" "2880,899.26" "1" "1" "180")
(command "_insert" "blkuc9" "2880,900" "1" "1" "0")
(command "_insert" "blkuc9" "2880,899.63" "1" "1" "180")
(command "_insert" "blkuc9" "2880,900.37" "1" "1" "0")
(command "_insert" "blkuc9" "2880,900" "1" "1" "180")
(command "_insert" "blkuc9" "2880,900.74" "1" "1" "0")
(command "_insert" "blkuc9" "2880,900.37" "1" "1" "180")
(command "_insert" "blkuc9" "2880,901.11" "1" "1" "0")
(command "_insert" "blkuc9" "2880,900.74" "1" "1" "180")
(command "_insert" "blkuc9" "2880,901.48" "1" "1" "0")
(command "_insert" "blkuc9" "2880,901.11" "1" "1" "180")
(command "_insert" "blkuc9" "2880,901.85" "1" "1" "0")
(command "_insert" "blkuc9" "2880,901.48" "1" "1" "180")
(command "_insert" "blkuc9" "2880,902.22" "1" "1" "0")
(command "_insert" "blkuc9" "2880,901.85" "1" "1" "180")
(command "_insert" "blkuc9" "2880,902.59" "1" "1" "0")
(command "_insert" "blkuc9" "2880,902.22" "1" "1" "180")
(command "_insert" "blkuc9" "2880,902.96" "1" "1" "0")
(command "_insert" "blkuc9" "2880,902.59" "1" "1" "180")
(command "_insert" "blkuc9" "2880,903.33" "1" "1" "0")
(command "_insert" "blkuc9" "2880,902.96" "1" "1" "180")
(command "_insert" "blkuc9" "2880,903.7" "1" "1" "0")
(command "_insert" "blkuc9" "2880,903.33" "1" "1" "180")
(command "_insert" "blkuc9" "2880,904.07" "1" "1" "0")
(command "_insert" "blkuc9" "2880,903.7" "1" "1" "180")
(command "_insert" "blkuc9" "2880,904.44" "1" "1" "0")
(command "_insert" "blkuc9" "2880,904.07" "1" "1" "180")
(command "_insert" "blkuc9" "2880,904.81" "1" "1" "0")
(command "_insert" "blkuc9" "2880,904.44" "1" "1" "180")
(command "_insert" "blkuc9" "2880,905.18" "1" "1" "0")
(command "_insert" "blkuc9" "2880,904.81" "1" "1" "180")
(command "_insert" "blkuc9" "2880,905.55" "1" "1" "0")
(command "_insert" "blkuc9" "2880,905.18" "1" "1" "180")
(command "_insert" "blkuc9" "2880,905.92" "1" "1" "0")
(command "_insert" "blkuc9" "2880,905.55" "1" "1" "180")
(command "_insert" "blkuc9" "2880,906.29" "1" "1" "0")
(command "_insert" "blkuc9" "2880,905.92" "1" "1" "180")
(command "_insert" "blkuc9" "2880,906.66" "1" "1" "0")
(command "_insert" "blkuc9" "2880,906.29" "1" "1" "180")
(command "_insert" "blkuc9" "2880,907.03" "1" "1" "0")
(command "_insert" "blkuc9" "2880,906.66" "1" "1" "180")
(command "_insert" "blkuc9" "2880,907.4" "1" "1" "0")
(command "_insert" "blkuc9" "2880,907.03" "1" "1" "180")
(command "_insert" "blkuc9" "2880,907.77" "1" "1" "0")
(command "_insert" "blkuc9" "2880,907.4" "1" "1" "180")
(command "_insert" "blkuc9" "2880,908.14" "1" "1" "0")
(command "_insert" "blkuc9" "2880,907.77" "1" "1" "180")
(command "_insert" "blkuc9" "2880,908.51" "1" "1" "0")
(command "_insert" "blkuc9" "2880,908.14" "1" "1" "180")
(command "_insert" "blkuc9" "2880,908.88" "1" "1" "0")
(command "_insert" "blkuc9" "2880,908.51" "1" "1" "180")
(command "_insert" "blkuc9" "2880,909.25" "1" "1" "0")
(command "_insert" "blkuc9" "2880,908.88" "1" "1" "180")
(command "_insert" "blkuc9" "2880,909.62" "1" "1" "0")
(command "_insert" "blkuc9" "2880,909.25" "1" "1" "180")
(command "_insert" "blkuc9" "2880,909.99" "1" "1" "0")
(command "_insert" "blkuc9" "2880,909.62" "1" "1" "180")
(command "_insert" "blkuc9" "2880,910.36" "1" "1" "0")
(command "_insert" "blkuc9" "2880,909.99" "1" "1" "180")
(command "_insert" "blkuc9" "2880,910.73" "1" "1" "0")
(command "_insert" "blkuc9" "2880,910.36" "1" "1" "180")
(command "_insert" "blkuc9" "2880,911.1" "1" "1" "0")
(command "_insert" "blkuc9" "2880,910.73" "1" "1" "180")
(command "_insert" "blkuc9" "2880,911.47" "1" "1" "0")
(command "_insert" "blkuc9" "2880,911.1" "1" "1" "180")
(command "_insert" "blkuc9" "2880,911.84" "1" "1" "0")
(command "_insert" "blkuc9" "2880,911.47" "1" "1" "180")
(command "_insert" "blkuc9" "2880,912.21" "1" "1" "0")
(command "_insert" "blkuc9" "2880,911.84" "1" "1" "180")
(command "_insert" "blkuc9" "2880,912.58" "1" "1" "0")
(command "_insert" "blkuc9" "2880,912.21" "1" "1" "180")
(command "_insert" "blkuc9" "2880,912.95" "1" "1" "0")
(command "_insert" "blkuc9" "2880,912.58" "1" "1" "180")
(command "_insert" "blkuc9" "2880,913.32" "1" "1" "0")
(command "_insert" "blkuc9" "2880,912.95" "1" "1" "180")
(command "_insert" "blkuc9" "2880,913.69" "1" "1" "0")
(command "_insert" "blkuc9" "2880,913.32" "1" "1" "180")
(command "_insert" "blkuc9" "2880,914.06" "1" "1" "0")
(command "_insert" "blkuc9" "2880,913.69" "1" "1" "180")
(command "_insert" "blkuc9" "2880,914.43" "1" "1" "0")
(command "_insert" "blkuc9" "2880,914.06" "1" "1" "180")
(command "_insert" "blkuc9" "2880,914.8" "1" "1" "0")
(command "_insert" "blkuc9" "2880,914.43" "1" "1" "180")
(command "_insert" "blkuc9" "2880,915.17" "1" "1" "0")
(command "_insert" "blkuc9" "2880,914.8" "1" "1" "180")
(command "_insert" "blkuc9" "2880,915.54" "1" "1" "0")
(command "_insert" "blkuc9" "2880,915.17" "1" "1" "180")
(command "_insert" "blkuc9" "2880,915.91" "1" "1" "0")
(command "_insert" "blkuc9" "2880,915.54" "1" "1" "180")
(command "_insert" "blkuc9" "2880,916.28" "1" "1" "0")
(command "_insert" "blkuc9" "2880,915.91" "1" "1" "180")
(command "_insert" "blkuc9" "2880,916.65" "1" "1" "0")
(command "_insert" "blkuc9" "2880,916.28" "1" "1" "180")
(command "_insert" "blkuc9" "2880,917.02" "1" "1" "0")
(command "_insert" "blkuc9" "2880,916.65" "1" "1" "180")
(command "_insert" "blkuc9" "2880,917.39" "1" "1" "0")
(command "_insert" "blkuc9" "2880,917.02" "1" "1" "180")
(command "_insert" "blkuc9" "2880,917.76" "1" "1" "0")
(command "_insert" "blkuc9" "2880,917.39" "1" "1" "180")
(command "_insert" "blkuc9" "2880,918.13" "1" "1" "0")
(command "_insert" "blkuc9" "2880,917.76" "1" "1" "180")
(command "_insert" "blkuc9" "2880,918.5" "1" "1" "0")
(command "_insert" "blkuc9" "2880,918.13" "1" "1" "180")
(command "_insert" "blkuc9" "2880,918.87" "1" "1" "0")
(command "_insert" "blkuc9" "2880,918.5" "1" "1" "180")
(command "_insert" "blkuc9" "2880,919.24" "1" "1" "0")
(command "_insert" "blkuc9" "2880,918.87" "1" "1" "180")
(command "_insert" "blkuc9" "2880,919.61" "1" "1" "0")
(command "_insert" "blkuc9" "2880,919.24" "1" "1" "180")
(command "_insert" "blkuc9" "2880,919.98" "1" "1" "0")
(command "_insert" "blkuc9" "2880,919.61" "1" "1" "180")
(command "_insert" "blkuc9" "2880,920.35" "1" "1" "0")
(command "_insert" "blkuc9" "2880,919.98" "1" "1" "180")
(command "_insert" "blkuc9" "2880,920.72" "1" "1" "0")
(command "_insert" "blkuc9" "2880,920.35" "1" "1" "180")
(command "_insert" "blkuc9" "2880,921.09" "1" "1" "0")
(command "_insert" "blkuc9" "2880,920.72" "1" "1" "180")
(command "_insert" "blkuc9" "2880,921.46" "1" "1" "0")
(command "_insert" "blkuc9" "2880,921.09" "1" "1" "180")
(command "_insert" "blkuc9" "2880,921.83" "1" "1" "0")
(command "_insert" "blkuc9" "2880,921.46" "1" "1" "180")
(command "_insert" "blkuc9" "2880,922.2" "1" "1" "0")
(command "_insert" "blkuc9" "2880,921.83" "1" "1" "180")
(command "_insert" "blkuc9" "2880,922.57" "1" "1" "0")
(command "_insert" "blkuc9" "2880,922.2" "1" "1" "180")
(command "_insert" "blkuc9" "2880,922.94" "1" "1" "0")
(command "_insert" "blkuc9" "2880,922.57" "1" "1" "180")
(command "_insert" "blkuc9" "2880,923.31" "1" "1" "0")
(command "_insert" "blkuc9" "2880,922.94" "1" "1" "180")
(command "_insert" "blkuc9" "2880,923.68" "1" "1" "0")
(command "_insert" "blkuc9" "2880,923.31" "1" "1" "180")
(command "_insert" "blkuc9" "2880,924.05" "1" "1" "0")
(command "_insert" "blkuc9" "2880,923.68" "1" "1" "180")
(command "_insert" "blkuc9" "2880,924.42" "1" "1" "0")
(command "_insert" "blkuc9" "2880,924.05" "1" "1" "180")
(command "_insert" "blkuc9" "2880,924.79" "1" "1" "0")
(command "_insert" "blkuc9" "2880,924.42" "1" "1" "180")
(command "_insert" "blkuc9" "2880,925.16" "1" "1" "0")
(command "_insert" "blkuc9" "2880,924.79" "1" "1" "180")
(command "_insert" "blkuc9" "2880,925.53" "1" "1" "0")
(command "_insert" "blkuc9" "2880,925.16" "1" "1" "180")
(command "_insert" "blkuc9" "2880,925.9" "1" "1" "0")
(command "_insert" "blkuc9" "2880,925.53" "1" "1" "180")
(command "_insert" "blkuc9" "2880,926.27" "1" "1" "0")
(command "_insert" "blkuc9" "2880,925.9" "1" "1" "180")
(command "_insert" "blkuc9" "2880,926.64" "1" "1" "0")
(command "_insert" "blkuc9" "2880,926.27" "1" "1" "180")
(command "_insert" "blkuc9" "2880,927.01" "1" "1" "0")
(command "_insert" "blkuc9" "2880,926.64" "1" "1" "180")
(command "_insert" "blkuc9" "2880,927.38" "1" "1" "0")
(command "_insert" "blkuc9" "2880,927.01" "1" "1" "180")
(command "_insert" "blkuc9" "2880,927.75" "1" "1" "0")
(command "_insert" "blkuc9" "2880,927.38" "1" "1" "180")
(command "_layer" "set" "phccover" "")
(command "_rectangle" "2878.914,933.3" "2881.086,866.7")
(command "_layer" "set" "nitride" "")
(setq phc9 currobj)
(command "_layer" "set" "cover" "")
(command "_rectangle" "2878.914,836.7" "2881.086,963.3")
(command "_layer" "set" "nitride" "")
(command "_layer" "set" "text" "")
(command "_circle" "2877.964,846.7" "0.075")
(command "_circle" "2877.589,846.7" "0.15")
(command "_circle" "2877.214,846.7" "0.075")
(command "_circle" "2876.839,846.7" "0.15")
(command "_circle" "2877.964,848.7" "0.075")
(command "_circle" "2877.589,848.7" "0.075")
(command "_circle" "2877.214,848.7" "0.15")
(command "_circle" "2876.839,848.7" "0.15")
(command "_circle" "2877.964,850.7" "0.075")
(command "_circle" "2877.589,850.7" "0.15")
(command "_circle" "2877.214,850.7" "0.15")
(command "_circle" "2876.839,850.7" "0.15")
(command "_circle" "2877.964,852.7" "0.075")
(command "_circle" "2877.589,852.7" "0.075")
(command "_circle" "2877.214,852.7" "0.075")
(command "_circle" "2876.839,852.7" "0.075")
(command "_circle" "2876.464,852.7" "0.15")
(command "_circle" "2877.964,854.7" "0.075")
(command "_circle" "2877.589,854.7" "0.15")
(command "_circle" "2877.214,854.7" "0.075")
(command "_circle" "2876.839,854.7" "0.075")
(command "_circle" "2876.464,854.7" "0.15")
(command "_circle" "2877.964,856.7" "0.075")
(command "_circle" "2877.589,856.7" "0.075")
(command "_circle" "2877.214,856.7" "0.15")
(command "_circle" "2876.839,856.7" "0.075")
(command "_circle" "2876.464,856.7" "0.15")
(command "_circle" "2877.964,858.7" "0.075")
(command "_circle" "2877.589,858.7" "0.15")
(command "_circle" "2877.214,858.7" "0.15")
(command "_circle" "2876.839,858.7" "0.075")
(command "_circle" "2876.464,858.7" "0.15")
(command "_circle" "2877.964,860.7" "0.075")
(command "_circle" "2877.589,860.7" "0.075")
(command "_circle" "2877.214,860.7" "0.075")
(command "_circle" "2876.839,860.7" "0.15")
(command "_circle" "2876.464,860.7" "0.15")
(command "_circle" "2877.964,862.7" "0.075")
(command "_circle" "2877.589,862.7" "0.15")
(command "_circle" "2877.214,862.7" "0.075")
(command "_circle" "2876.839,862.7" "0.15")
(command "_circle" "2876.464,862.7" "0.15")
(command "_circle" "2877.964,864.7" "0.075")
(command "_circle" "2877.589,864.7" "0.075")
(command "_circle" "2877.214,864.7" "0.15")
(command "_circle" "2876.839,864.7" "0.15")
(command "_circle" "2876.464,864.7" "0.15")
(command "_circle" "2877.964,866.7" "0.075")
(command "_circle" "2877.589,866.7" "0.15")
(command "_circle" "2877.214,866.7" "0.15")
(command "_circle" "2876.839,866.7" "0.15")
(command "_circle" "2876.464,866.7" "0.15")
(command "_circle" "2877.964,868.7" "0.075")
(command "_circle" "2877.589,868.7" "0.075")
(command "_circle" "2877.214,868.7" "0.075")
(command "_circle" "2876.839,868.7" "0.075")
(command "_circle" "2876.464,868.7" "0.075")
(command "_circle" "2876.089,868.7" "0.15")
(command "_circle" "2877.964,870.7" "0.075")
(command "_circle" "2877.589,870.7" "0.15")
(command "_circle" "2877.214,870.7" "0.075")
(command "_circle" "2876.839,870.7" "0.075")
(command "_circle" "2876.464,870.7" "0.075")
(command "_circle" "2876.089,870.7" "0.15")
(command "_circle" "2877.964,872.7" "0.075")
(command "_circle" "2877.589,872.7" "0.075")
(command "_circle" "2877.214,872.7" "0.15")
(command "_circle" "2876.839,872.7" "0.075")
(command "_circle" "2876.464,872.7" "0.075")
(command "_circle" "2876.089,872.7" "0.15")
(command "_circle" "2877.964,874.7" "0.075")
(command "_circle" "2877.589,874.7" "0.15")
(command "_circle" "2877.214,874.7" "0.15")
(command "_circle" "2876.839,874.7" "0.075")
(command "_circle" "2876.464,874.7" "0.075")
(command "_circle" "2876.089,874.7" "0.15")
(command "_circle" "2877.964,876.7" "0.075")
(command "_circle" "2877.589,876.7" "0.075")
(command "_circle" "2877.214,876.7" "0.075")
(command "_circle" "2876.839,876.7" "0.15")
(command "_circle" "2876.464,876.7" "0.075")
(command "_circle" "2876.089,876.7" "0.15")
(command "_circle" "2877.964,878.7" "0.075")
(command "_circle" "2877.589,878.7" "0.15")
(command "_circle" "2877.214,878.7" "0.075")
(command "_circle" "2876.839,878.7" "0.15")
(command "_circle" "2876.464,878.7" "0.075")
(command "_circle" "2876.089,878.7" "0.15")
(command "_circle" "2877.964,880.7" "0.075")
(command "_circle" "2877.589,880.7" "0.075")
(command "_circle" "2877.214,880.7" "0.15")
(command "_circle" "2876.839,880.7" "0.15")
(command "_circle" "2876.464,880.7" "0.075")
(command "_circle" "2876.089,880.7" "0.15")
(command "_circle" "2877.964,882.7" "0.075")
(command "_circle" "2877.589,882.7" "0.15")
(command "_circle" "2877.214,882.7" "0.15")
(command "_circle" "2876.839,882.7" "0.15")
(command "_circle" "2876.464,882.7" "0.075")
(command "_circle" "2876.089,882.7" "0.15")
(command "_circle" "2877.964,884.7" "0.075")
(command "_circle" "2877.589,884.7" "0.075")
(command "_circle" "2877.214,884.7" "0.075")
(command "_circle" "2876.839,884.7" "0.075")
(command "_circle" "2876.464,884.7" "0.15")
(command "_circle" "2876.089,884.7" "0.15")
(command "_circle" "2877.964,886.7" "0.075")
(command "_circle" "2877.589,886.7" "0.15")
(command "_circle" "2877.214,886.7" "0.075")
(command "_circle" "2876.839,886.7" "0.075")
(command "_circle" "2876.464,886.7" "0.15")
(command "_circle" "2876.089,886.7" "0.15")
(command "_circle" "2877.964,888.7" "0.075")
(command "_circle" "2877.589,888.7" "0.075")
(command "_circle" "2877.214,888.7" "0.15")
(command "_circle" "2876.839,888.7" "0.075")
(command "_circle" "2876.464,888.7" "0.15")
(command "_circle" "2876.089,888.7" "0.15")
(command "_circle" "2877.964,890.7" "0.075")
(command "_circle" "2877.589,890.7" "0.15")
(command "_circle" "2877.214,890.7" "0.15")
(command "_circle" "2876.839,890.7" "0.075")
(command "_circle" "2876.464,890.7" "0.15")
(command "_circle" "2876.089,890.7" "0.15")
(command "_circle" "2877.964,892.7" "0.075")
(command "_circle" "2877.589,892.7" "0.075")
(command "_circle" "2877.214,892.7" "0.075")
(command "_circle" "2876.839,892.7" "0.15")
(command "_circle" "2876.464,892.7" "0.15")
(command "_circle" "2876.089,892.7" "0.15")
(command "_circle" "2877.964,894.7" "0.075")
(command "_circle" "2877.589,894.7" "0.15")
(command "_circle" "2877.214,894.7" "0.075")
(command "_circle" "2876.839,894.7" "0.15")
(command "_circle" "2876.464,894.7" "0.15")
(command "_circle" "2876.089,894.7" "0.15")
(command "_circle" "2877.964,896.7" "0.075")
(command "_circle" "2877.589,896.7" "0.075")
(command "_circle" "2877.214,896.7" "0.15")
(command "_circle" "2876.839,896.7" "0.15")
(command "_circle" "2876.464,896.7" "0.15")
(command "_circle" "2876.089,896.7" "0.15")
(command "_circle" "2877.964,898.7" "0.075")
(command "_circle" "2877.589,898.7" "0.15")
(command "_circle" "2877.214,898.7" "0.15")
(command "_circle" "2876.839,898.7" "0.15")
(command "_circle" "2876.464,898.7" "0.15")
(command "_circle" "2876.089,898.7" "0.15")
(command "_circle" "2877.964,900.7" "0.075")
(command "_circle" "2877.589,900.7" "0.075")
(command "_circle" "2877.214,900.7" "0.075")
(command "_circle" "2876.839,900.7" "0.075")
(command "_circle" "2876.464,900.7" "0.075")
(command "_circle" "2876.089,900.7" "0.075")
(command "_circle" "2875.714,900.7" "0.15")
(command "_circle" "2877.964,902.7" "0.075")
(command "_circle" "2877.589,902.7" "0.15")
(command "_circle" "2877.214,902.7" "0.075")
(command "_circle" "2876.839,902.7" "0.075")
(command "_circle" "2876.464,902.7" "0.075")
(command "_circle" "2876.089,902.7" "0.075")
(command "_circle" "2875.714,902.7" "0.15")
(command "_circle" "2877.964,904.7" "0.075")
(command "_circle" "2877.589,904.7" "0.075")
(command "_circle" "2877.214,904.7" "0.15")
(command "_circle" "2876.839,904.7" "0.075")
(command "_circle" "2876.464,904.7" "0.075")
(command "_circle" "2876.089,904.7" "0.075")
(command "_circle" "2875.714,904.7" "0.15")
(command "_circle" "2877.964,906.7" "0.075")
(command "_circle" "2877.589,906.7" "0.15")
(command "_circle" "2877.214,906.7" "0.15")
(command "_circle" "2876.839,906.7" "0.075")
(command "_circle" "2876.464,906.7" "0.075")
(command "_circle" "2876.089,906.7" "0.075")
(command "_circle" "2875.714,906.7" "0.15")
(command "_circle" "2877.964,908.7" "0.075")
(command "_circle" "2877.589,908.7" "0.075")
(command "_circle" "2877.214,908.7" "0.075")
(command "_circle" "2876.839,908.7" "0.15")
(command "_circle" "2876.464,908.7" "0.075")
(command "_circle" "2876.089,908.7" "0.075")
(command "_circle" "2875.714,908.7" "0.15")
(command "_circle" "2877.964,910.7" "0.075")
(command "_circle" "2877.589,910.7" "0.15")
(command "_circle" "2877.214,910.7" "0.075")
(command "_circle" "2876.839,910.7" "0.15")
(command "_circle" "2876.464,910.7" "0.075")
(command "_circle" "2876.089,910.7" "0.075")
(command "_circle" "2875.714,910.7" "0.15")
(command "_circle" "2877.964,912.7" "0.075")
(command "_circle" "2877.589,912.7" "0.075")
(command "_circle" "2877.214,912.7" "0.15")
(command "_circle" "2876.839,912.7" "0.15")
(command "_circle" "2876.464,912.7" "0.075")
(command "_circle" "2876.089,912.7" "0.075")
(command "_circle" "2875.714,912.7" "0.15")
(command "_circle" "2877.964,914.7" "0.075")
(command "_circle" "2877.589,914.7" "0.15")
(command "_circle" "2877.214,914.7" "0.15")
(command "_circle" "2876.839,914.7" "0.15")
(command "_circle" "2876.464,914.7" "0.075")
(command "_circle" "2876.089,914.7" "0.075")
(command "_circle" "2875.714,914.7" "0.15")
(command "_circle" "2877.964,916.7" "0.075")
(command "_circle" "2877.589,916.7" "0.075")
(command "_circle" "2877.214,916.7" "0.075")
(command "_circle" "2876.839,916.7" "0.075")
(command "_circle" "2876.464,916.7" "0.15")
(command "_circle" "2876.089,916.7" "0.075")
(command "_circle" "2875.714,916.7" "0.15")
(command "_circle" "2877.964,918.7" "0.075")
(command "_circle" "2877.589,918.7" "0.15")
(command "_circle" "2877.214,918.7" "0.075")
(command "_circle" "2876.839,918.7" "0.075")
(command "_circle" "2876.464,918.7" "0.15")
(command "_circle" "2876.089,918.7" "0.075")
(command "_circle" "2875.714,918.7" "0.15")
(command "_circle" "2877.964,920.7" "0.075")
(command "_circle" "2877.589,920.7" "0.075")
(command "_circle" "2877.214,920.7" "0.15")
(command "_circle" "2876.839,920.7" "0.075")
(command "_circle" "2876.464,920.7" "0.15")
(command "_circle" "2876.089,920.7" "0.075")
(command "_circle" "2875.714,920.7" "0.15")
(command "_circle" "2877.964,922.7" "0.075")
(command "_circle" "2877.589,922.7" "0.15")
(command "_circle" "2877.214,922.7" "0.15")
(command "_circle" "2876.839,922.7" "0.075")
(command "_circle" "2876.464,922.7" "0.15")
(command "_circle" "2876.089,922.7" "0.075")
(command "_circle" "2875.714,922.7" "0.15")
(command "_circle" "2877.964,924.7" "0.075")
(command "_circle" "2877.589,924.7" "0.075")
(command "_circle" "2877.214,924.7" "0.075")
(command "_circle" "2876.839,924.7" "0.15")
(command "_circle" "2876.464,924.7" "0.15")
(command "_circle" "2876.089,924.7" "0.075")
(command "_circle" "2875.714,924.7" "0.15")
(command "_circle" "2877.964,926.7" "0.075")
(command "_circle" "2877.589,926.7" "0.15")
(command "_circle" "2877.214,926.7" "0.075")
(command "_circle" "2876.839,926.7" "0.15")
(command "_circle" "2876.464,926.7" "0.15")
(command "_circle" "2876.089,926.7" "0.075")
(command "_circle" "2875.714,926.7" "0.15")
(command "_circle" "2877.964,928.7" "0.075")
(command "_circle" "2877.589,928.7" "0.075")
(command "_circle" "2877.214,928.7" "0.15")
(command "_circle" "2876.839,928.7" "0.15")
(command "_circle" "2876.464,928.7" "0.15")
(command "_circle" "2876.089,928.7" "0.075")
(command "_circle" "2875.714,928.7" "0.15")
(command "_circle" "2877.964,930.7" "0.075")
(command "_circle" "2877.589,930.7" "0.15")
(command "_circle" "2877.214,930.7" "0.15")
(command "_circle" "2876.839,930.7" "0.15")
(command "_circle" "2876.464,930.7" "0.15")
(command "_circle" "2876.089,930.7" "0.075")
(command "_circle" "2875.714,930.7" "0.15")
(command "_circle" "2877.964,932.7" "0.075")
(command "_circle" "2877.589,932.7" "0.075")
(command "_circle" "2877.214,932.7" "0.075")
(command "_circle" "2876.839,932.7" "0.075")
(command "_circle" "2876.464,932.7" "0.075")
(command "_circle" "2876.089,932.7" "0.15")
(command "_circle" "2875.714,932.7" "0.15")
(command "_circle" "2877.964,934.7" "0.075")
(command "_circle" "2877.589,934.7" "0.15")
(command "_circle" "2877.214,934.7" "0.075")
(command "_circle" "2876.839,934.7" "0.075")
(command "_circle" "2876.464,934.7" "0.075")
(command "_circle" "2876.089,934.7" "0.15")
(command "_circle" "2875.714,934.7" "0.15")
(command "_circle" "2877.964,936.7" "0.075")
(command "_circle" "2877.589,936.7" "0.075")
(command "_circle" "2877.214,936.7" "0.15")
(command "_circle" "2876.839,936.7" "0.075")
(command "_circle" "2876.464,936.7" "0.075")
(command "_circle" "2876.089,936.7" "0.15")
(command "_circle" "2875.714,936.7" "0.15")
(command "_circle" "2877.964,938.7" "0.075")
(command "_circle" "2877.589,938.7" "0.15")
(command "_circle" "2877.214,938.7" "0.15")
(command "_circle" "2876.839,938.7" "0.075")
(command "_circle" "2876.464,938.7" "0.075")
(command "_circle" "2876.089,938.7" "0.15")
(command "_circle" "2875.714,938.7" "0.15")
(command "_circle" "2877.964,940.7" "0.075")
(command "_circle" "2877.589,940.7" "0.075")
(command "_circle" "2877.214,940.7" "0.075")
(command "_circle" "2876.839,940.7" "0.15")
(command "_circle" "2876.464,940.7" "0.075")
(command "_circle" "2876.089,940.7" "0.15")
(command "_circle" "2875.714,940.7" "0.15")
(command "_circle" "2877.964,942.7" "0.075")
(command "_circle" "2877.589,942.7" "0.15")
(command "_circle" "2877.214,942.7" "0.075")
(command "_circle" "2876.839,942.7" "0.15")
(command "_circle" "2876.464,942.7" "0.075")
(command "_circle" "2876.089,942.7" "0.15")
(command "_circle" "2875.714,942.7" "0.15")
(command "_circle" "2877.964,944.7" "0.075")
(command "_circle" "2877.589,944.7" "0.075")
(command "_circle" "2877.214,944.7" "0.15")
(command "_circle" "2876.839,944.7" "0.15")
(command "_circle" "2876.464,944.7" "0.075")
(command "_circle" "2876.089,944.7" "0.15")
(command "_circle" "2875.714,944.7" "0.15")
(command "_circle" "2877.964,946.7" "0.075")
(command "_circle" "2877.589,946.7" "0.15")
(command "_circle" "2877.214,946.7" "0.15")
(command "_circle" "2876.839,946.7" "0.15")
(command "_circle" "2876.464,946.7" "0.075")
(command "_circle" "2876.089,946.7" "0.15")
(command "_circle" "2875.714,946.7" "0.15")
(command "_circle" "2877.964,948.7" "0.075")
(command "_circle" "2877.589,948.7" "0.075")
(command "_circle" "2877.214,948.7" "0.075")
(command "_circle" "2876.839,948.7" "0.075")
(command "_circle" "2876.464,948.7" "0.15")
(command "_circle" "2876.089,948.7" "0.15")
(command "_circle" "2875.714,948.7" "0.15")
(command "_circle" "2877.964,950.7" "0.075")
(command "_circle" "2877.589,950.7" "0.15")
(command "_circle" "2877.214,950.7" "0.075")
(command "_circle" "2876.839,950.7" "0.075")
(command "_circle" "2876.464,950.7" "0.15")
(command "_circle" "2876.089,950.7" "0.15")
(command "_circle" "2875.714,950.7" "0.15")
(command "_circle" "2877.964,952.7" "0.075")
(command "_circle" "2877.589,952.7" "0.075")
(command "_circle" "2877.214,952.7" "0.15")
(command "_circle" "2876.839,952.7" "0.075")
(command "_circle" "2876.464,952.7" "0.15")
(command "_circle" "2876.089,952.7" "0.15")
(command "_circle" "2875.714,952.7" "0.15")
(command "_circle" "2877.964,954.7" "0.075")
(command "_circle" "2877.589,954.7" "0.15")
(command "_circle" "2877.214,954.7" "0.15")
(command "_circle" "2876.839,954.7" "0.075")
(command "_circle" "2876.464,954.7" "0.15")
(command "_circle" "2876.089,954.7" "0.15")
(command "_circle" "2875.714,954.7" "0.15")
(command "_circle" "2877.964,956.7" "0.075")
(command "_circle" "2877.589,956.7" "0.075")
(command "_circle" "2877.214,956.7" "0.075")
(command "_circle" "2876.839,956.7" "0.15")
(command "_circle" "2876.464,956.7" "0.15")
(command "_circle" "2876.089,956.7" "0.15")
(command "_circle" "2875.714,956.7" "0.15")
(command "_circle" "2877.964,958.7" "0.075")
(command "_circle" "2877.589,958.7" "0.15")
(command "_circle" "2877.214,958.7" "0.075")
(command "_circle" "2876.839,958.7" "0.15")
(command "_circle" "2876.464,958.7" "0.15")
(command "_circle" "2876.089,958.7" "0.15")
(command "_circle" "2875.714,958.7" "0.15")
(command "_circle" "2877.964,960.7" "0.075")
(command "_circle" "2877.589,960.7" "0.075")
(command "_circle" "2877.214,960.7" "0.15")
(command "_circle" "2876.839,960.7" "0.15")
(command "_circle" "2876.464,960.7" "0.15")
(command "_circle" "2876.089,960.7" "0.15")
(command "_circle" "2875.714,960.7" "0.15")
(command "_circle" "2877.964,962.7" "0.075")
(command "_circle" "2877.589,962.7" "0.15")
(command "_circle" "2877.214,962.7" "0.15")
(command "_circle" "2876.839,962.7" "0.15")
(command "_circle" "2876.464,962.7" "0.15")
(command "_circle" "2876.089,962.7" "0.15")
(command "_circle" "2875.714,962.7" "0.15")
(command "_layer" "set" "nitride" "")
(command "_layer" "set" "text" "")
(command-s "_text" "2866.914,963.3" "2" "-90" "a = 370 nm" )
(sssetfirst nil (ssget "_L"))
(if (not (numberp (vl-string-search "Mac" (getvar "platform")))) (c:txtexp))
(command "_layer" "set" "nitride" "")
(command "_layer" "set" "text" "")
(command-s "_text" "2863.914,963.3" "2" "-90" "gap = 270 nm" )
(sssetfirst nil (ssget "_L"))
(if (not (numberp (vl-string-search "Mac" (getvar "platform")))) (c:txtexp))
(command "_layer" "set" "nitride" "")
(command "_layer" "set" "text" "")
(command-s "_text" "2860.914,963.3" "2" "-90" "amplitude = 122 nm" )
(sssetfirst nil (ssget "_L"))
(if (not (numberp (vl-string-search "Mac" (getvar "platform")))) (c:txtexp))
(command "_layer" "set" "nitride" "")
(command "_layer" "set" "text" "")
(command-s "_text" "2857.914,963.3" "2" "-90" "start width = 280 nm" )
(sssetfirst nil (ssget "_L"))
(if (not (numberp (vl-string-search "Mac" (getvar "platform")))) (c:txtexp))
(command "_layer" "set" "nitride" "")
(command "_layer" "set" "text" "")
(command-s "_text" "2854.914,963.3" "2" "-90" "width = 286 nm" )
(sssetfirst nil (ssget "_L"))
(if (not (numberp (vl-string-search "Mac" (getvar "platform")))) (c:txtexp))
(command "_layer" "set" "nitride" "")
(command "_layer" "set" "text" "")
(command-s "_text" "2851.914,963.3" "2" "-90" "taper: 15" )
(sssetfirst nil (ssget "_L"))
(if (not (numberp (vl-string-search "Mac" (getvar "platform")))) (c:txtexp))
(command "_layer" "set" "nitride" "")
(command "_layer" "set" "text" "")
(command-s "_text" "2848.914,963.3" "2" "-90" "nominal: 150" )
(sssetfirst nil (ssget "_L"))
(if (not (numberp (vl-string-search "Mac" (getvar "platform")))) (c:txtexp))
(command "_layer" "set" "nitride" "")
(command "_layer" "set" "indicators" "")
(setq coords (list 
(list 2800.415 940) 
(list 2800.415 920) 
(list 2780.415 900) 
(list 2800.415 880) 
(list 2800.415 860) 
(list 2800.415 900) 
(list 2800.415 887.0711) 
(list 2787.4861 900) 
(list 2800.415 912.9289) 
(list 2800.415 900)))
(apply 'command (append '("pline") coords '("c")))
(command "._fillet" "radius" "1" "._fillet" "P" (entlast))
(setq coords (list 
(list 2959.585 940) 
(list 2959.585 920) 
(list 2979.585 900) 
(list 2959.585 880) 
(list 2959.585 860) 
(list 2959.585 900) 
(list 2959.585 887.0711) 
(list 2972.5139 900) 
(list 2959.585 912.9289) 
(list 2959.585 900)))
(apply 'command (append '("pline") coords '("c")))
(command "._fillet" "radius" "1" "._fillet" "P" (entlast))
(command "_layer" "set" "holes" "")
(command "_circle" "2798.0629,914.1124" "0.5")
(command "_circle" "2795.7109,911.7603" "0.5")
(command "_circle" "2793.3588,909.4083" "0.5")
(command "_circle" "2791.0067,907.0562" "0.5")
(command "_circle" "2788.6547,904.7041" "0.5")
(command "_circle" "2786.3026,902.3521" "0.5")
(command "_circle" "2783.9505,900" "0.5")
(command "_circle" "2786.3026,897.6479" "0.5")
(command "_circle" "2788.6547,895.2959" "0.5")
(command "_circle" "2791.0067,892.9438" "0.5")
(command "_circle" "2793.3588,890.5917" "0.5")
(command "_circle" "2795.7109,888.2397" "0.5")
(command "_circle" "2798.0629,885.8876" "0.5")
(command "_circle" "2961.9371,914.1124" "0.5")
(command "_circle" "2964.2891,911.7603" "0.5")
(command "_circle" "2966.6412,909.4083" "0.5")
(command "_circle" "2968.9933,907.0562" "0.5")
(command "_circle" "2971.3453,904.7041" "0.5")
(command "_circle" "2973.6974,902.3521" "0.5")
(command "_circle" "2976.0495,900" "0.5")
(command "_circle" "2973.6974,897.6479" "0.5")
(command "_circle" "2971.3453,895.2959" "0.5")
(command "_circle" "2968.9933,892.9438" "0.5")
(command "_circle" "2966.6412,890.5917" "0.5")
(command "_circle" "2964.2891,888.2397" "0.5")
(command "_circle" "2961.9371,885.8876" "0.5")
(command "_layer" "set" "nitride" "")
(command "_block" "blkcoupler9" "2880,900" coupler9 "")
(command "_insert" "blkcoupler9" "2880,900" "1" "1" "0")
(command "_insert" "blkcoupler9" "2880,900" "1" "1" "180")
(command "_block" "blksinglenanobeam9" "2880,900" singlenanobeam9 "")
(command "_insert" "blksinglenanobeam9" "2880,900" "1" "1" "0")
(command "_insert" "blksinglenanobeam9" "2880,900" "1" "1" "180")
(command "_block" "blkanglednodearray9" "2880,900" anglednodearray9 "")
(command "_insert" "blkanglednodearray9" "2880,900" "1" "1" "0")
(command "_insert" "blkanglednodearray9" "2880,900" "1" "1" "180")
(command "_block" "blkcooledsinglenanobeam9" "2880,900" cooledsinglenanobeam9 "")
(command "_insert" "blkcooledsinglenanobeam9" "2880,900" "1" "1" "0")
(command "_insert" "blkcooledsinglenanobeam9" "2880,900" "1" "1" "180")
(command "_block" "blkyjunction9" "2880,900" yjunction9 "")
(command "_insert" "blkyjunction9" "2880,900" "1" "1" "0")
(command "_insert" "blkyjunction9" "2880,900" "1" "1" "180")
; DRAWING BULGING VEE GROOVE
(command "_layer" "set" "vgroove" "")
(setq coords (list 
(list 2805.415 -605) 
(list 2805.415 0) 
(list 2805.415 0) 
(list 2805.415 1800) 
(list 2805.415 1800) 
(list 2805.415 2405) 
(list 2954.585 2405) 
(list 2954.585 1800) 
(list 2954.585 1800) 
(list 2954.585 0) 
(list 2954.585 0) 
(list 2954.585 -605)))
(apply 'command (append '("pline") coords '("c")))
(command "._fillet" "radius" "0" "._fillet" "P" (entlast))
(command "_layer" "set" "window" "")
(command "_rectangle" "2805.415,-1935" "2954.585,-600")
(command "_rectangle" "2805.415,2400" "2954.585,5300")
(command "_layer" "set" "grid" "")
(command "_rectangle" "2806.415,-1934" "2829.9433,-1909.2133")
(command "_array" "last" "" "R" "75" "3" "25.7867" "24.5283")
(command "_rectangle" "2881,-1934" "2904.5283,-1909.2133")
(command "_array" "last" "" "R" "75" "3" "25.7867" "24.5283")
(command "_rectangle" "2806.415,1" "2829.9433,25.7")
(command "_array" "last" "" "R" "70" "3" "25.7" "24.5283")
(command "_rectangle" "2881,1" "2904.5283,25.7")
(command "_array" "last" "" "R" "70" "3" "25.7" "24.5283")
(command "_rectangle" "2806.415,1801" "2829.9433,1825.9185")
(command "_array" "last" "" "R" "135" "3" "25.9185" "24.5283")
(command "_rectangle" "2881,1801" "2904.5283,1825.9185")
(command "_array" "last" "" "R" "135" "3" "25.9185" "24.5283")
(command "_layer" "set" "vgrooveFDA" "")
(command "_rectangle" "2954.585,-2233" "2805.415,-1933")
(command "_layer" "set" "nitride" "")
(command "_layer" "set" "holes" "")
(command "_circle" "2957.085,331.5" "0.5")
(command "_array" "last" "" "R" "379" "1" "3" "2.5")
(command "_circle" "2802.915,331.5" "0.5")
(command "_array" "last" "" "R" "379" "1" "3" "-2.5")
(command "_layer" "set" "nitride" "")
(command "_layer" "set" "window" "")
(command "_layer" "set" "window" "")
(command "_rectangle" "2959.585,0" "3120.415,1800")
(command "._fillet" "radius" "20" "._fillet" "P" (entlast))
(command "_layer" "set" "grid" "")
(command "_rectangle" "2960.585,1" "2982.4179,25.7")
(command "_array" "last" "" "R" "70" "7" "25.7" "22.8329")
(command "_layer" "set" "nitride" "")
; DRAWING REGION LAYER
(command "_layer" "set" "regionLayer9" "")
(command "_rectangle" "2800,-460" "2960,2260")
(command "_layer" "set" "nitride" "")
(setq coupler9 nil)
(setq singlenanobeam9 nil)
(setq anglednodearray9 nil)
(setq cooledsinglenanobeam9 nil)
(setq yjunction9 nil)
; DEVICE #10
(command "_layer" "set" "window" "")
(command "_circle" "3112.915,-415" "5")
(command "_circle" "3112.915,-402.5" "5")
(command "_circle" "3112.915,-390" "5")
(command "_circle" "3112.915,-377.5" "5")
(command "_circle" "3100.415,-415" "5")
(command "_circle" "3100.415,-402.5" "5")
(command "_circle" "3100.415,-390" "5")
(command "_circle" "3100.415,-377.5" "5")
(command "_circle" "3087.915,-415" "5")
(command "_circle" "3087.915,-402.5" "5")
(command "_layer" "set" "nitride" "")
(setq currobj nil)
(setq currobj (ssadd))
; DRAWING COUPLER
(setq coords (list 
(list 3200.0635 -415) 
(list 3200.0635 -413) 
(list 3273.585 -413) 
(list 3273.585 -413) 
(list 3273.9677 -413.0761) 
(list 3274.2921 -413.2929) 
(list 3274.5089 -413.6173) 
(list 3274.585 -414) 
(list 3274.585 -411.8) 
(list 3274.585 -411.8) 
(list 3274.5089 -412.1827) 
(list 3274.2921 -412.5071) 
(list 3273.9677 -412.7239) 
(list 3273.585 -412.8) 
(list 3200.0635 -412.8) 
(list 3200.0635 -410.8) 
(list 3199.9365 -410.8) 
(list 3199.9365 -412.8) 
(list 3126.415 -412.8) 
(list 3126.0323 -412.7239) 
(list 3125.7079 -412.5071) 
(list 3125.4911 -412.1827) 
(list 3125.415 -411.8) 
(list 3125.415 -411.8) 
(list 3125.415 -414) 
(list 3125.4911 -413.6173) 
(list 3125.7079 -413.2929) 
(list 3126.0323 -413.0761) 
(list 3126.415 -413) 
(list 3126.415 -413) 
(list 3199.9365 -413) 
(list 3199.9365 -415)))
(apply 'command (append '("pline") coords '("c")))
(setq currobj (ssadd (entlast) currobj))
(command "._fillet" "radius" "0.3" "._fillet" "P" (entlast))
(command "_layer" "set" "holes" "")
(command "_circle" "3200,-412.9" "0.113")
(setq currobj (ssadd (entlast) currobj))
(command "_layer" "set" "nitride" "")
(command "_layer" "set" "text" "")
(command "_circle" "3199.2,-415" "0.075")
(command "_circle" "3199.2,-414.7" "0.075")
(command "_circle" "3199.2,-414.4" "0.075")
(command "_circle" "3198.9,-415" "0.075")
(command "_circle" "3198.9,-414.7" "0.075")
(command "_circle" "3198.9,-414.4" "0.075")
(command "_circle" "3198.6,-415" "0.075")
(command "_circle" "3198.6,-414.7" "0.075")
(command "_circle" "3198.6,-414.4" "0.075")
(command "_layer" "set" "nitride" "")
(command "_layer" "set" "prebias" "")
(command "_rectangle" "3125.415,-414" "3274.585,-411.8")
(setq currobj (ssadd (entlast) currobj))
(command "_rectangle" "3199.9365,-415" "3200.0635,-410.8")
(setq currobj (ssadd (entlast) currobj))
(command "_layer" "set" "nitride" "")
(setq coupler10 currobj)
(setq currobj nil)
(setq currobj (ssadd))
; DRAWING SINGLE NANOBEAM
(setq coords (list 
(list 3200.0635 -410.8) 
(list 3200.0635 -409.1417) 
(list 3200.0635 -407.4833) 
(list 3200.0635 -405.825) 
(list 3200.0635 -404.1667) 
(list 3200.0635 -402.5083) 
(list 3200.0635 -400.85) 
(list 3200.0635 -399.1917) 
(list 3200.0635 -397.5333) 
(list 3200.0636 -395.875) 
(list 3200.0636 -394.2167) 
(list 3200.0636 -392.5583) 
(list 3200.0636 -390.9) 
(list 3200.0637 -389.2417) 
(list 3200.0637 -387.5833) 
(list 3200.0637 -385.925) 
(list 3200.0638 -384.2667) 
(list 3200.0638 -382.6083) 
(list 3200.0639 -380.95) 
(list 3200.064 -379.2917) 
(list 3200.0641 -377.6333) 
(list 3200.0642 -375.975) 
(list 3200.0642 -374.3167) 
(list 3200.0644 -372.6583) 
(list 3200.0645 -371) 
(list 3200.0646 -369.3417) 
(list 3200.0647 -367.6833) 
(list 3200.0649 -366.025) 
(list 3200.065 -364.3667) 
(list 3200.0652 -362.7083) 
(list 3200.0654 -361.05) 
(list 3200.0656 -359.3917) 
(list 3200.0658 -357.7333) 
(list 3200.066 -356.075) 
(list 3200.0663 -354.4167) 
(list 3200.0665 -352.7583) 
(list 3200.0668 -351.1) 
(list 3200.0671 -349.4417) 
(list 3200.0674 -347.7833) 
(list 3200.0677 -346.125) 
(list 3200.068 -344.4667) 
(list 3200.0683 -342.8083) 
(list 3200.0687 -341.15) 
(list 3200.0691 -339.4917) 
(list 3200.0695 -337.8333) 
(list 3200.0699 -336.175) 
(list 3200.0703 -334.5167) 
(list 3200.0708 -332.8583) 
(list 3200.0713 -331.2) 
(list 3200.0718 -329.5417) 
(list 3200.0723 -327.8833) 
(list 3200.0728 -326.225) 
(list 3200.0734 -324.5667) 
(list 3200.074 -322.9083) 
(list 3200.0746 -321.25) 
(list 3200.0752 -319.5917) 
(list 3200.0758 -317.9333) 
(list 3200.0765 -316.275) 
(list 3200.0772 -314.6167) 
(list 3200.0779 -312.9583) 
(list 3200.0787 -311.3) 
(list 3200.0795 -309.6417) 
(list 3200.0803 -307.9833) 
(list 3200.0811 -306.325) 
(list 3200.0819 -304.6667) 
(list 3200.0828 -303.0083) 
(list 3200.0837 -301.35) 
(list 3200.0846 -299.6917) 
(list 3200.0856 -298.0333) 
(list 3200.0866 -296.375) 
(list 3200.0876 -294.7167) 
(list 3200.0887 -293.0583) 
(list 3200.0897 -291.4) 
(list 3200.0909 -289.7417) 
(list 3200.092 -288.0833) 
(list 3200.0932 -286.425) 
(list 3200.0944 -284.7667) 
(list 3200.0956 -283.1083) 
(list 3200.0969 -281.45) 
(list 3200.0982 -279.7917) 
(list 3200.0995 -278.1333) 
(list 3200.1009 -276.475) 
(list 3200.1023 -274.8167) 
(list 3200.1037 -273.1583) 
(list 3200.1052 -271.5) 
(list 3200.1067 -269.8417) 
(list 3200.1082 -268.1833) 
(list 3200.1098 -266.525) 
(list 3200.1114 -264.8667) 
(list 3200.1131 -263.2083) 
(list 3200.1148 -261.55) 
(list 3200.1165 -259.8917) 
(list 3200.1183 -258.2333) 
(list 3200.1201 -256.575) 
(list 3200.1219 -254.9167) 
(list 3200.1238 -253.2583) 
(list 3200.1257 -251.6) 
(list 3200.1277 -249.9417) 
(list 3200.1297 -248.2833) 
(list 3200.1317 -246.625) 
(list 3200.1338 -244.9667) 
(list 3200.1359 -243.3083) 
(list 3200.1381 -241.65) 
(list 3200.1403 -239.9917) 
(list 3200.1426 -238.3333) 
(list 3200.1449 -236.675) 
(list 3200.1472 -235.0167) 
(list 3200.1496 -233.3583) 
(list 3200.1521 -231.7) 
(list 3200.1546 -230.0417) 
(list 3200.1571 -228.3833) 
(list 3200.1597 -226.725) 
(list 3200.1623 -225.0667) 
(list 3200.165 -223.4083) 
(list 3200.1677 -221.75) 
(list 3200.1704 -220.0917) 
(list 3200.1733 -218.4333) 
(list 3200.1761 -216.775) 
(list 3200.179 -215.1167) 
(list 3200.182 -213.4583) 
(list 3200.185 -211.8) 
(list 3199.815 -211.8) 
(list 3199.818 -213.4583) 
(list 3199.821 -215.1167) 
(list 3199.8239 -216.775) 
(list 3199.8268 -218.4333) 
(list 3199.8296 -220.0917) 
(list 3199.8323 -221.75) 
(list 3199.835 -223.4083) 
(list 3199.8377 -225.0667) 
(list 3199.8403 -226.725) 
(list 3199.8429 -228.3833) 
(list 3199.8454 -230.0417) 
(list 3199.8479 -231.7) 
(list 3199.8504 -233.3583) 
(list 3199.8528 -235.0167) 
(list 3199.8551 -236.675) 
(list 3199.8574 -238.3333) 
(list 3199.8597 -239.9917) 
(list 3199.8619 -241.65) 
(list 3199.8641 -243.3083) 
(list 3199.8662 -244.9667) 
(list 3199.8683 -246.625) 
(list 3199.8703 -248.2833) 
(list 3199.8723 -249.9417) 
(list 3199.8743 -251.6) 
(list 3199.8762 -253.2583) 
(list 3199.8781 -254.9167) 
(list 3199.8799 -256.575) 
(list 3199.8817 -258.2333) 
(list 3199.8835 -259.8917) 
(list 3199.8852 -261.55) 
(list 3199.8869 -263.2083) 
(list 3199.8886 -264.8667) 
(list 3199.8902 -266.525) 
(list 3199.8918 -268.1833) 
(list 3199.8933 -269.8417) 
(list 3199.8948 -271.5) 
(list 3199.8963 -273.1583) 
(list 3199.8977 -274.8167) 
(list 3199.8991 -276.475) 
(list 3199.9005 -278.1333) 
(list 3199.9018 -279.7917) 
(list 3199.9031 -281.45) 
(list 3199.9044 -283.1083) 
(list 3199.9056 -284.7667) 
(list 3199.9068 -286.425) 
(list 3199.908 -288.0833) 
(list 3199.9091 -289.7417) 
(list 3199.9103 -291.4) 
(list 3199.9113 -293.0583) 
(list 3199.9124 -294.7167) 
(list 3199.9134 -296.375) 
(list 3199.9144 -298.0333) 
(list 3199.9154 -299.6917) 
(list 3199.9163 -301.35) 
(list 3199.9172 -303.0083) 
(list 3199.9181 -304.6667) 
(list 3199.9189 -306.325) 
(list 3199.9197 -307.9833) 
(list 3199.9205 -309.6417) 
(list 3199.9213 -311.3) 
(list 3199.9221 -312.9583) 
(list 3199.9228 -314.6167) 
(list 3199.9235 -316.275) 
(list 3199.9242 -317.9333) 
(list 3199.9248 -319.5917) 
(list 3199.9254 -321.25) 
(list 3199.926 -322.9083) 
(list 3199.9266 -324.5667) 
(list 3199.9272 -326.225) 
(list 3199.9277 -327.8833) 
(list 3199.9282 -329.5417) 
(list 3199.9287 -331.2) 
(list 3199.9292 -332.8583) 
(list 3199.9297 -334.5167) 
(list 3199.9301 -336.175) 
(list 3199.9305 -337.8333) 
(list 3199.9309 -339.4917) 
(list 3199.9313 -341.15) 
(list 3199.9317 -342.8083) 
(list 3199.932 -344.4667) 
(list 3199.9323 -346.125) 
(list 3199.9326 -347.7833) 
(list 3199.9329 -349.4417) 
(list 3199.9332 -351.1) 
(list 3199.9335 -352.7583) 
(list 3199.9337 -354.4167) 
(list 3199.934 -356.075) 
(list 3199.9342 -357.7333) 
(list 3199.9344 -359.3917) 
(list 3199.9346 -361.05) 
(list 3199.9348 -362.7083) 
(list 3199.935 -364.3667) 
(list 3199.9351 -366.025) 
(list 3199.9353 -367.6833) 
(list 3199.9354 -369.3417) 
(list 3199.9355 -371) 
(list 3199.9356 -372.6583) 
(list 3199.9358 -374.3167) 
(list 3199.9358 -375.975) 
(list 3199.9359 -377.6333) 
(list 3199.936 -379.2917) 
(list 3199.9361 -380.95) 
(list 3199.9362 -382.6083) 
(list 3199.9362 -384.2667) 
(list 3199.9363 -385.925) 
(list 3199.9363 -387.5833) 
(list 3199.9363 -389.2417) 
(list 3199.9364 -390.9) 
(list 3199.9364 -392.5583) 
(list 3199.9364 -394.2167) 
(list 3199.9364 -395.875) 
(list 3199.9365 -397.5333) 
(list 3199.9365 -399.1917) 
(list 3199.9365 -400.85) 
(list 3199.9365 -402.5083) 
(list 3199.9365 -404.1667) 
(list 3199.9365 -405.825) 
(list 3199.9365 -407.4833) 
(list 3199.9365 -409.1417) 
(list 3199.9365 -410.8)))
(apply 'command (append '("pline") coords '("c")))
(setq currobj (ssadd (entlast) currobj))
(command "_layer" "set" "prebias" "")
(command "_rectangle" "3199.815,-410.8" "3200.185,-211.8")
(setq currobj (ssadd (entlast) currobj))
(command "_layer" "set" "nitride" "")
(setq singlenanobeam10 currobj)
(setq currobj nil)
(setq currobj (ssadd))
; DRAWING NODE ARRAY
(setq coords (list 
(list 3200.185 -211.8) 
(list 3200.5625 -201.8) 
(list 3200.5625 -201.8) 
(list 3200.5625 -200.8) 
(list 3274.585 -212.6864) 
(list 3274.585 -207.7434) 
(list 3200.5625 -197.357) 
(list 3200.5625 -196.357) 
(list 3200.5625 -196.357) 
(list 3200.2625 -186.357) 
(list 3199.7375 -186.357) 
(list 3199.4375 -196.357) 
(list 3199.4375 -196.357) 
(list 3199.4375 -197.357) 
(list 3125.415 -207.7434) 
(list 3125.415 -212.6864) 
(list 3199.4375 -200.8) 
(list 3199.4375 -201.8) 
(list 3199.4375 -201.8) 
(list 3199.815 -211.8)))
(apply 'command (append '("pline") coords '("c")))
(setq currobj (ssadd (entlast) currobj))
(command "_layer" "set" "prebias" "")
(setq coords (list 
(list 3199.4375 -212.6864) 
(list 3199.4375 -200.8) 
(list 3125.415 -212.6864) 
(list 3125.415 -207.7434) 
(list 3199.4375 -197.357) 
(list 3199.4375 -186.357) 
(list 3200.5625 -186.357) 
(list 3200.5625 -197.357) 
(list 3274.585 -207.7434) 
(list 3274.585 -212.6864) 
(list 3200.5625 -200.8) 
(list 3200.5625 -212.6864)))
(apply 'command (append '("pline") coords '("c")))
(setq currobj (ssadd (entlast) currobj))
(command "_layer" "set" "nitride" "")
(command "_layer" "set" "fda1" "")
(setq coords (list 
(list 3200.5625 -200.657) 
(list 3274.585 -212.5434) 
(list 3274.585 -212.3664) 
(list 3200.5625 -200.58)))
(apply 'command (append '("pline") coords '("c")))
(setq currobj (ssadd (entlast) currobj))
(setq coords (list 
(list 3200.5625 -200.437) 
(list 3274.585 -212.2234) 
(list 3274.585 -212.0464) 
(list 3200.5625 -200.36)))
(apply 'command (append '("pline") coords '("c")))
(setq currobj (ssadd (entlast) currobj))
(setq coords (list 
(list 3200.5625 -200.217) 
(list 3274.585 -211.9034) 
(list 3274.585 -211.7264) 
(list 3200.5625 -200.14)))
(apply 'command (append '("pline") coords '("c")))
(setq currobj (ssadd (entlast) currobj))
(setq coords (list 
(list 3200.5625 -199.997) 
(list 3274.585 -211.5834) 
(list 3274.585 -211.4064) 
(list 3200.5625 -199.92)))
(apply 'command (append '("pline") coords '("c")))
(setq currobj (ssadd (entlast) currobj))
(setq coords (list 
(list 3200.5625 -199.777) 
(list 3274.585 -211.2634) 
(list 3274.585 -211.0864) 
(list 3200.5625 -199.7)))
(apply 'command (append '("pline") coords '("c")))
(setq currobj (ssadd (entlast) currobj))
(setq coords (list 
(list 3200.5625 -199.557) 
(list 3274.585 -210.9434) 
(list 3274.585 -210.7664) 
(list 3200.5625 -199.48)))
(apply 'command (append '("pline") coords '("c")))
(setq currobj (ssadd (entlast) currobj))
(setq coords (list 
(list 3200.5625 -199.337) 
(list 3274.585 -210.6234) 
(list 3274.585 -210.4464) 
(list 3200.5625 -199.26)))
(apply 'command (append '("pline") coords '("c")))
(setq currobj (ssadd (entlast) currobj))
(setq coords (list 
(list 3200.5625 -199.117) 
(list 3274.585 -210.3034) 
(list 3274.585 -210.1264) 
(list 3200.5625 -199.04)))
(apply 'command (append '("pline") coords '("c")))
(setq currobj (ssadd (entlast) currobj))
(setq coords (list 
(list 3200.5625 -198.897) 
(list 3274.585 -209.9834) 
(list 3274.585 -209.8064) 
(list 3200.5625 -198.82)))
(apply 'command (append '("pline") coords '("c")))
(setq currobj (ssadd (entlast) currobj))
(setq coords (list 
(list 3200.5625 -198.677) 
(list 3274.585 -209.6634) 
(list 3274.585 -209.4864) 
(list 3200.5625 -198.6)))
(apply 'command (append '("pline") coords '("c")))
(setq currobj (ssadd (entlast) currobj))
(setq coords (list 
(list 3200.5625 -198.457) 
(list 3274.585 -209.3434) 
(list 3274.585 -209.1664) 
(list 3200.5625 -198.38)))
(apply 'command (append '("pline") coords '("c")))
(setq currobj (ssadd (entlast) currobj))
(setq coords (list 
(list 3200.5625 -198.237) 
(list 3274.585 -209.0234) 
(list 3274.585 -208.8464) 
(list 3200.5625 -198.16)))
(apply 'command (append '("pline") coords '("c")))
(setq currobj (ssadd (entlast) currobj))
(setq coords (list 
(list 3200.5625 -198.017) 
(list 3274.585 -208.7034) 
(list 3274.585 -208.5264) 
(list 3200.5625 -197.94)))
(apply 'command (append '("pline") coords '("c")))
(setq currobj (ssadd (entlast) currobj))
(setq coords (list 
(list 3200.5625 -197.797) 
(list 3274.585 -208.3834) 
(list 3274.585 -208.2064) 
(list 3200.5625 -197.72)))
(apply 'command (append '("pline") coords '("c")))
(setq currobj (ssadd (entlast) currobj))
(setq coords (list 
(list 3200.5625 -197.577) 
(list 3274.585 -208.0634) 
(list 3274.585 -207.8864) 
(list 3200.5625 -197.5)))
(apply 'command (append '("pline") coords '("c")))
(setq currobj (ssadd (entlast) currobj))
(setq coords (list 
(list 3199.4375 -197.5) 
(list 3125.415 -207.8864) 
(list 3125.415 -208.0634) 
(list 3199.4375 -197.577)))
(apply 'command (append '("pline") coords '("c")))
(setq currobj (ssadd (entlast) currobj))
(setq coords (list 
(list 3199.4375 -197.72) 
(list 3125.415 -208.2064) 
(list 3125.415 -208.3834) 
(list 3199.4375 -197.797)))
(apply 'command (append '("pline") coords '("c")))
(setq currobj (ssadd (entlast) currobj))
(setq coords (list 
(list 3199.4375 -197.94) 
(list 3125.415 -208.5264) 
(list 3125.415 -208.7034) 
(list 3199.4375 -198.017)))
(apply 'command (append '("pline") coords '("c")))
(setq currobj (ssadd (entlast) currobj))
(setq coords (list 
(list 3199.4375 -198.16) 
(list 3125.415 -208.8464) 
(list 3125.415 -209.0234) 
(list 3199.4375 -198.237)))
(apply 'command (append '("pline") coords '("c")))
(setq currobj (ssadd (entlast) currobj))
(setq coords (list 
(list 3199.4375 -198.38) 
(list 3125.415 -209.1664) 
(list 3125.415 -209.3434) 
(list 3199.4375 -198.457)))
(apply 'command (append '("pline") coords '("c")))
(setq currobj (ssadd (entlast) currobj))
(setq coords (list 
(list 3199.4375 -198.6) 
(list 3125.415 -209.4864) 
(list 3125.415 -209.6634) 
(list 3199.4375 -198.677)))
(apply 'command (append '("pline") coords '("c")))
(setq currobj (ssadd (entlast) currobj))
(setq coords (list 
(list 3199.4375 -198.82) 
(list 3125.415 -209.8064) 
(list 3125.415 -209.9834) 
(list 3199.4375 -198.897)))
(apply 'command (append '("pline") coords '("c")))
(setq currobj (ssadd (entlast) currobj))
(setq coords (list 
(list 3199.4375 -199.04) 
(list 3125.415 -210.1264) 
(list 3125.415 -210.3034) 
(list 3199.4375 -199.117)))
(apply 'command (append '("pline") coords '("c")))
(setq currobj (ssadd (entlast) currobj))
(setq coords (list 
(list 3199.4375 -199.26) 
(list 3125.415 -210.4464) 
(list 3125.415 -210.6234) 
(list 3199.4375 -199.337)))
(apply 'command (append '("pline") coords '("c")))
(setq currobj (ssadd (entlast) currobj))
(setq coords (list 
(list 3199.4375 -199.48) 
(list 3125.415 -210.7664) 
(list 3125.415 -210.9434) 
(list 3199.4375 -199.557)))
(apply 'command (append '("pline") coords '("c")))
(setq currobj (ssadd (entlast) currobj))
(setq coords (list 
(list 3199.4375 -199.7) 
(list 3125.415 -211.0864) 
(list 3125.415 -211.2634) 
(list 3199.4375 -199.777)))
(apply 'command (append '("pline") coords '("c")))
(setq currobj (ssadd (entlast) currobj))
(setq coords (list 
(list 3199.4375 -199.92) 
(list 3125.415 -211.4064) 
(list 3125.415 -211.5834) 
(list 3199.4375 -199.997)))
(apply 'command (append '("pline") coords '("c")))
(setq currobj (ssadd (entlast) currobj))
(setq coords (list 
(list 3199.4375 -200.14) 
(list 3125.415 -211.7264) 
(list 3125.415 -211.9034) 
(list 3199.4375 -200.217)))
(apply 'command (append '("pline") coords '("c")))
(setq currobj (ssadd (entlast) currobj))
(setq coords (list 
(list 3199.4375 -200.36) 
(list 3125.415 -212.0464) 
(list 3125.415 -212.2234) 
(list 3199.4375 -200.437)))
(apply 'command (append '("pline") coords '("c")))
(setq currobj (ssadd (entlast) currobj))
(setq coords (list 
(list 3199.4375 -200.58) 
(list 3125.415 -212.3664) 
(list 3125.415 -212.5434) 
(list 3199.4375 -200.657)))
(apply 'command (append '("pline") coords '("c")))
(setq currobj (ssadd (entlast) currobj))
(command "_layer" "set" "nitride" "")
(command "_layer" "set" "text" "")
(command "_circle" "3198.985,-211.8" "0.075")
(command "_circle" "3198.985,-211.5" "0.075")
(command "_circle" "3198.985,-211.2" "0.075")
(command "_circle" "3198.985,-210.9" "0.075")
(command "_circle" "3198.985,-210.6" "0.075")
(command "_circle" "3198.685,-211.8" "0.075")
(command "_circle" "3198.685,-211.5" "0.075")
(command "_circle" "3198.685,-211.2" "0.075")
(command "_circle" "3198.685,-210.9" "0.075")
(command "_circle" "3198.685,-210.6" "0.075")
(command "_circle" "3198.385,-211.8" "0.075")
(command "_circle" "3198.385,-211.5" "0.075")
(command "_circle" "3198.385,-211.2" "0.075")
(command "_circle" "3198.385,-210.9" "0.075")
(command "_circle" "3198.385,-210.6" "0.075")
(command "_circle" "3198.085,-211.8" "0.075")
(command "_circle" "3198.085,-211.5" "0.075")
(command "_circle" "3198.085,-211.2" "0.075")
(command "_circle" "3198.085,-210.9" "0.075")
(command "_circle" "3198.085,-210.6" "0.075")
(command "_circle" "3197.785,-211.8" "0.075")
(command "_circle" "3197.785,-211.5" "0.075")
(command "_circle" "3197.785,-211.2" "0.075")
(command "_circle" "3197.785,-210.9" "0.075")
(command "_circle" "3197.785,-210.6" "0.075")
(command "_layer" "set" "nitride" "")
(setq anglednodearray10 currobj)
(setq currobj nil)
(setq currobj (ssadd))
; DRAWING COOLED SINGLE NANOBEAM
(setq coords (list 
(list 3200.2625 -186.357) 
(list 3200.2625 -181.357) 
(list 3199.7375 -181.357) 
(list 3199.7375 -186.357)))
(apply 'command (append '("pline") coords '("c")))
(setq currobj (ssadd (entlast) currobj))
(command "_layer" "set" "prebias" "")
(command "_rectangle" "3199.7375,-186.357" "3200.2625,-181.357")
(setq currobj (ssadd (entlast) currobj))
(command "_layer" "set" "nitride" "")
(setq coords (list 
(list 3200.2625 -181.357) 
(list 3200.5625 -171.357) 
(list 3200.5625 -171.357) 
(list 3200.5625 -170.357) 
(list 3274.585 -171.107) 
(list 3274.585 -166.164) 
(list 3200.5625 -166.914) 
(list 3200.5625 -165.914) 
(list 3200.5625 -165.914) 
(list 3200.2625 -155.914) 
(list 3199.7375 -155.914) 
(list 3199.4375 -165.914) 
(list 3199.4375 -165.914) 
(list 3199.4375 -166.914) 
(list 3125.415 -166.164) 
(list 3125.415 -171.107) 
(list 3199.4375 -170.357) 
(list 3199.4375 -171.357) 
(list 3199.4375 -171.357) 
(list 3199.7375 -181.357)))
(apply 'command (append '("pline") coords '("c")))
(setq currobj (ssadd (entlast) currobj))
(command "_layer" "set" "prebias" "")
(setq coords (list 
(list 3199.4375 -181.357) 
(list 3199.4375 -170.357) 
(list 3125.415 -171.107) 
(list 3125.415 -166.164) 
(list 3199.4375 -166.914) 
(list 3199.4375 -155.914) 
(list 3200.5625 -155.914) 
(list 3200.5625 -166.914) 
(list 3274.585 -166.164) 
(list 3274.585 -171.107) 
(list 3200.5625 -170.357) 
(list 3200.5625 -181.357)))
(apply 'command (append '("pline") coords '("c")))
(setq currobj (ssadd (entlast) currobj))
(command "_layer" "set" "nitride" "")
(command "_layer" "set" "fda1" "")
(setq coords (list 
(list 3200.5625 -170.214) 
(list 3274.585 -170.964) 
(list 3274.585 -170.787) 
(list 3200.5625 -170.137)))
(apply 'command (append '("pline") coords '("c")))
(setq currobj (ssadd (entlast) currobj))
(setq coords (list 
(list 3200.5625 -169.994) 
(list 3274.585 -170.644) 
(list 3274.585 -170.467) 
(list 3200.5625 -169.917)))
(apply 'command (append '("pline") coords '("c")))
(setq currobj (ssadd (entlast) currobj))
(setq coords (list 
(list 3200.5625 -169.774) 
(list 3274.585 -170.324) 
(list 3274.585 -170.147) 
(list 3200.5625 -169.697)))
(apply 'command (append '("pline") coords '("c")))
(setq currobj (ssadd (entlast) currobj))
(setq coords (list 
(list 3200.5625 -169.554) 
(list 3274.585 -170.004) 
(list 3274.585 -169.827) 
(list 3200.5625 -169.477)))
(apply 'command (append '("pline") coords '("c")))
(setq currobj (ssadd (entlast) currobj))
(setq coords (list 
(list 3200.5625 -169.334) 
(list 3274.585 -169.684) 
(list 3274.585 -169.507) 
(list 3200.5625 -169.257)))
(apply 'command (append '("pline") coords '("c")))
(setq currobj (ssadd (entlast) currobj))
(setq coords (list 
(list 3200.5625 -169.114) 
(list 3274.585 -169.364) 
(list 3274.585 -169.187) 
(list 3200.5625 -169.037)))
(apply 'command (append '("pline") coords '("c")))
(setq currobj (ssadd (entlast) currobj))
(setq coords (list 
(list 3200.5625 -168.894) 
(list 3274.585 -169.044) 
(list 3274.585 -168.867) 
(list 3200.5625 -168.817)))
(apply 'command (append '("pline") coords '("c")))
(setq currobj (ssadd (entlast) currobj))
(setq coords (list 
(list 3200.5625 -168.674) 
(list 3274.585 -168.724) 
(list 3274.585 -168.547) 
(list 3200.5625 -168.597)))
(apply 'command (append '("pline") coords '("c")))
(setq currobj (ssadd (entlast) currobj))
(setq coords (list 
(list 3200.5625 -168.454) 
(list 3274.585 -168.404) 
(list 3274.585 -168.227) 
(list 3200.5625 -168.377)))
(apply 'command (append '("pline") coords '("c")))
(setq currobj (ssadd (entlast) currobj))
(setq coords (list 
(list 3200.5625 -168.234) 
(list 3274.585 -168.084) 
(list 3274.585 -167.907) 
(list 3200.5625 -168.157)))
(apply 'command (append '("pline") coords '("c")))
(setq currobj (ssadd (entlast) currobj))
(setq coords (list 
(list 3200.5625 -168.014) 
(list 3274.585 -167.764) 
(list 3274.585 -167.587) 
(list 3200.5625 -167.937)))
(apply 'command (append '("pline") coords '("c")))
(setq currobj (ssadd (entlast) currobj))
(setq coords (list 
(list 3200.5625 -167.794) 
(list 3274.585 -167.444) 
(list 3274.585 -167.267) 
(list 3200.5625 -167.717)))
(apply 'command (append '("pline") coords '("c")))
(setq currobj (ssadd (entlast) currobj))
(setq coords (list 
(list 3200.5625 -167.574) 
(list 3274.585 -167.124) 
(list 3274.585 -166.947) 
(list 3200.5625 -167.497)))
(apply 'command (append '("pline") coords '("c")))
(setq currobj (ssadd (entlast) currobj))
(setq coords (list 
(list 3200.5625 -167.354) 
(list 3274.585 -166.804) 
(list 3274.585 -166.627) 
(list 3200.5625 -167.277)))
(apply 'command (append '("pline") coords '("c")))
(setq currobj (ssadd (entlast) currobj))
(setq coords (list 
(list 3200.5625 -167.134) 
(list 3274.585 -166.484) 
(list 3274.585 -166.307) 
(list 3200.5625 -167.057)))
(apply 'command (append '("pline") coords '("c")))
(setq currobj (ssadd (entlast) currobj))
(setq coords (list 
(list 3199.4375 -167.057) 
(list 3125.415 -166.307) 
(list 3125.415 -166.484) 
(list 3199.4375 -167.134)))
(apply 'command (append '("pline") coords '("c")))
(setq currobj (ssadd (entlast) currobj))
(setq coords (list 
(list 3199.4375 -167.277) 
(list 3125.415 -166.627) 
(list 3125.415 -166.804) 
(list 3199.4375 -167.354)))
(apply 'command (append '("pline") coords '("c")))
(setq currobj (ssadd (entlast) currobj))
(setq coords (list 
(list 3199.4375 -167.497) 
(list 3125.415 -166.947) 
(list 3125.415 -167.124) 
(list 3199.4375 -167.574)))
(apply 'command (append '("pline") coords '("c")))
(setq currobj (ssadd (entlast) currobj))
(setq coords (list 
(list 3199.4375 -167.717) 
(list 3125.415 -167.267) 
(list 3125.415 -167.444) 
(list 3199.4375 -167.794)))
(apply 'command (append '("pline") coords '("c")))
(setq currobj (ssadd (entlast) currobj))
(setq coords (list 
(list 3199.4375 -167.937) 
(list 3125.415 -167.587) 
(list 3125.415 -167.764) 
(list 3199.4375 -168.014)))
(apply 'command (append '("pline") coords '("c")))
(setq currobj (ssadd (entlast) currobj))
(setq coords (list 
(list 3199.4375 -168.157) 
(list 3125.415 -167.907) 
(list 3125.415 -168.084) 
(list 3199.4375 -168.234)))
(apply 'command (append '("pline") coords '("c")))
(setq currobj (ssadd (entlast) currobj))
(setq coords (list 
(list 3199.4375 -168.377) 
(list 3125.415 -168.227) 
(list 3125.415 -168.404) 
(list 3199.4375 -168.454)))
(apply 'command (append '("pline") coords '("c")))
(setq currobj (ssadd (entlast) currobj))
(setq coords (list 
(list 3199.4375 -168.597) 
(list 3125.415 -168.547) 
(list 3125.415 -168.724) 
(list 3199.4375 -168.674)))
(apply 'command (append '("pline") coords '("c")))
(setq currobj (ssadd (entlast) currobj))
(setq coords (list 
(list 3199.4375 -168.817) 
(list 3125.415 -168.867) 
(list 3125.415 -169.044) 
(list 3199.4375 -168.894)))
(apply 'command (append '("pline") coords '("c")))
(setq currobj (ssadd (entlast) currobj))
(setq coords (list 
(list 3199.4375 -169.037) 
(list 3125.415 -169.187) 
(list 3125.415 -169.364) 
(list 3199.4375 -169.114)))
(apply 'command (append '("pline") coords '("c")))
(setq currobj (ssadd (entlast) currobj))
(setq coords (list 
(list 3199.4375 -169.257) 
(list 3125.415 -169.507) 
(list 3125.415 -169.684) 
(list 3199.4375 -169.334)))
(apply 'command (append '("pline") coords '("c")))
(setq currobj (ssadd (entlast) currobj))
(setq coords (list 
(list 3199.4375 -169.477) 
(list 3125.415 -169.827) 
(list 3125.415 -170.004) 
(list 3199.4375 -169.554)))
(apply 'command (append '("pline") coords '("c")))
(setq currobj (ssadd (entlast) currobj))
(setq coords (list 
(list 3199.4375 -169.697) 
(list 3125.415 -170.147) 
(list 3125.415 -170.324) 
(list 3199.4375 -169.774)))
(apply 'command (append '("pline") coords '("c")))
(setq currobj (ssadd (entlast) currobj))
(setq coords (list 
(list 3199.4375 -169.917) 
(list 3125.415 -170.467) 
(list 3125.415 -170.644) 
(list 3199.4375 -169.994)))
(apply 'command (append '("pline") coords '("c")))
(setq currobj (ssadd (entlast) currobj))
(setq coords (list 
(list 3199.4375 -170.137) 
(list 3125.415 -170.787) 
(list 3125.415 -170.964) 
(list 3199.4375 -170.214)))
(apply 'command (append '("pline") coords '("c")))
(setq currobj (ssadd (entlast) currobj))
(command "_layer" "set" "nitride" "")
(command "_layer" "set" "text" "")
(command "_circle" "3199.0625,-181.357" "0.075")
(command "_circle" "3199.0625,-181.057" "0.075")
(command "_circle" "3199.0625,-180.757" "0.075")
(command "_circle" "3199.0625,-180.457" "0.075")
(command "_circle" "3199.0625,-180.157" "0.075")
(command "_circle" "3198.7625,-181.357" "0.075")
(command "_circle" "3198.7625,-181.057" "0.075")
(command "_circle" "3198.7625,-180.757" "0.075")
(command "_circle" "3198.7625,-180.457" "0.075")
(command "_circle" "3198.7625,-180.157" "0.075")
(command "_circle" "3198.4625,-181.357" "0.075")
(command "_circle" "3198.4625,-181.057" "0.075")
(command "_circle" "3198.4625,-180.757" "0.075")
(command "_circle" "3198.4625,-180.457" "0.075")
(command "_circle" "3198.4625,-180.157" "0.075")
(command "_circle" "3198.1625,-181.357" "0.075")
(command "_circle" "3198.1625,-181.057" "0.075")
(command "_circle" "3198.1625,-180.757" "0.075")
(command "_circle" "3198.1625,-180.457" "0.075")
(command "_circle" "3198.1625,-180.157" "0.075")
(command "_circle" "3197.8625,-181.357" "0.075")
(command "_circle" "3197.8625,-181.057" "0.075")
(command "_circle" "3197.8625,-180.757" "0.075")
(command "_circle" "3197.8625,-180.457" "0.075")
(command "_circle" "3197.8625,-180.157" "0.075")
(command "_layer" "set" "nitride" "")
(setq coords (list 
(list 3200.2625 -155.914) 
(list 3200.2625 -40.2693) 
(list 3199.7375 -40.2693) 
(list 3199.7375 -155.914)))
(apply 'command (append '("pline") coords '("c")))
(setq currobj (ssadd (entlast) currobj))
(command "_layer" "set" "prebias" "")
(command "_rectangle" "3199.7375,-155.914" "3200.2625,-40.2693")
(setq currobj (ssadd (entlast) currobj))
(command "_layer" "set" "nitride" "")
(setq coords (list 
(list 3200.2625 -40.2693) 
(list 3200.5625 -30.2693) 
(list 3200.5625 -30.2693) 
(list 3200.5625 -29.2693) 
(list 3274.585 -30.0193) 
(list 3274.585 -25.0763) 
(list 3200.5625 -25.8263) 
(list 3200.5625 -24.8263) 
(list 3200.5625 -24.8263) 
(list 3200.2625 -14.8263) 
(list 3199.7375 -14.8263) 
(list 3199.4375 -24.8263) 
(list 3199.4375 -24.8263) 
(list 3199.4375 -25.8263) 
(list 3125.415 -25.0763) 
(list 3125.415 -30.0193) 
(list 3199.4375 -29.2693) 
(list 3199.4375 -30.2693) 
(list 3199.4375 -30.2693) 
(list 3199.7375 -40.2693)))
(apply 'command (append '("pline") coords '("c")))
(setq currobj (ssadd (entlast) currobj))
(command "_layer" "set" "prebias" "")
(setq coords (list 
(list 3199.4375 -40.2693) 
(list 3199.4375 -29.2693) 
(list 3125.415 -30.0193) 
(list 3125.415 -25.0763) 
(list 3199.4375 -25.8263) 
(list 3199.4375 -14.8263) 
(list 3200.5625 -14.8263) 
(list 3200.5625 -25.8263) 
(list 3274.585 -25.0763) 
(list 3274.585 -30.0193) 
(list 3200.5625 -29.2693) 
(list 3200.5625 -40.2693)))
(apply 'command (append '("pline") coords '("c")))
(setq currobj (ssadd (entlast) currobj))
(command "_layer" "set" "nitride" "")
(command "_layer" "set" "fda1" "")
(setq coords (list 
(list 3200.5625 -29.1263) 
(list 3274.585 -29.8763) 
(list 3274.585 -29.6993) 
(list 3200.5625 -29.0493)))
(apply 'command (append '("pline") coords '("c")))
(setq currobj (ssadd (entlast) currobj))
(setq coords (list 
(list 3200.5625 -28.9063) 
(list 3274.585 -29.5563) 
(list 3274.585 -29.3793) 
(list 3200.5625 -28.8293)))
(apply 'command (append '("pline") coords '("c")))
(setq currobj (ssadd (entlast) currobj))
(setq coords (list 
(list 3200.5625 -28.6863) 
(list 3274.585 -29.2363) 
(list 3274.585 -29.0593) 
(list 3200.5625 -28.6093)))
(apply 'command (append '("pline") coords '("c")))
(setq currobj (ssadd (entlast) currobj))
(setq coords (list 
(list 3200.5625 -28.4663) 
(list 3274.585 -28.9163) 
(list 3274.585 -28.7393) 
(list 3200.5625 -28.3893)))
(apply 'command (append '("pline") coords '("c")))
(setq currobj (ssadd (entlast) currobj))
(setq coords (list 
(list 3200.5625 -28.2463) 
(list 3274.585 -28.5963) 
(list 3274.585 -28.4193) 
(list 3200.5625 -28.1693)))
(apply 'command (append '("pline") coords '("c")))
(setq currobj (ssadd (entlast) currobj))
(setq coords (list 
(list 3200.5625 -28.0263) 
(list 3274.585 -28.2763) 
(list 3274.585 -28.0993) 
(list 3200.5625 -27.9493)))
(apply 'command (append '("pline") coords '("c")))
(setq currobj (ssadd (entlast) currobj))
(setq coords (list 
(list 3200.5625 -27.8063) 
(list 3274.585 -27.9563) 
(list 3274.585 -27.7793) 
(list 3200.5625 -27.7293)))
(apply 'command (append '("pline") coords '("c")))
(setq currobj (ssadd (entlast) currobj))
(setq coords (list 
(list 3200.5625 -27.5863) 
(list 3274.585 -27.6363) 
(list 3274.585 -27.4593) 
(list 3200.5625 -27.5093)))
(apply 'command (append '("pline") coords '("c")))
(setq currobj (ssadd (entlast) currobj))
(setq coords (list 
(list 3200.5625 -27.3663) 
(list 3274.585 -27.3163) 
(list 3274.585 -27.1393) 
(list 3200.5625 -27.2893)))
(apply 'command (append '("pline") coords '("c")))
(setq currobj (ssadd (entlast) currobj))
(setq coords (list 
(list 3200.5625 -27.1463) 
(list 3274.585 -26.9963) 
(list 3274.585 -26.8193) 
(list 3200.5625 -27.0693)))
(apply 'command (append '("pline") coords '("c")))
(setq currobj (ssadd (entlast) currobj))
(setq coords (list 
(list 3200.5625 -26.9263) 
(list 3274.585 -26.6763) 
(list 3274.585 -26.4993) 
(list 3200.5625 -26.8493)))
(apply 'command (append '("pline") coords '("c")))
(setq currobj (ssadd (entlast) currobj))
(setq coords (list 
(list 3200.5625 -26.7063) 
(list 3274.585 -26.3563) 
(list 3274.585 -26.1793) 
(list 3200.5625 -26.6293)))
(apply 'command (append '("pline") coords '("c")))
(setq currobj (ssadd (entlast) currobj))
(setq coords (list 
(list 3200.5625 -26.4863) 
(list 3274.585 -26.0363) 
(list 3274.585 -25.8593) 
(list 3200.5625 -26.4093)))
(apply 'command (append '("pline") coords '("c")))
(setq currobj (ssadd (entlast) currobj))
(setq coords (list 
(list 3200.5625 -26.2663) 
(list 3274.585 -25.7163) 
(list 3274.585 -25.5393) 
(list 3200.5625 -26.1893)))
(apply 'command (append '("pline") coords '("c")))
(setq currobj (ssadd (entlast) currobj))
(setq coords (list 
(list 3200.5625 -26.0463) 
(list 3274.585 -25.3963) 
(list 3274.585 -25.2193) 
(list 3200.5625 -25.9693)))
(apply 'command (append '("pline") coords '("c")))
(setq currobj (ssadd (entlast) currobj))
(setq coords (list 
(list 3199.4375 -25.9693) 
(list 3125.415 -25.2193) 
(list 3125.415 -25.3963) 
(list 3199.4375 -26.0463)))
(apply 'command (append '("pline") coords '("c")))
(setq currobj (ssadd (entlast) currobj))
(setq coords (list 
(list 3199.4375 -26.1893) 
(list 3125.415 -25.5393) 
(list 3125.415 -25.7163) 
(list 3199.4375 -26.2663)))
(apply 'command (append '("pline") coords '("c")))
(setq currobj (ssadd (entlast) currobj))
(setq coords (list 
(list 3199.4375 -26.4093) 
(list 3125.415 -25.8593) 
(list 3125.415 -26.0363) 
(list 3199.4375 -26.4863)))
(apply 'command (append '("pline") coords '("c")))
(setq currobj (ssadd (entlast) currobj))
(setq coords (list 
(list 3199.4375 -26.6293) 
(list 3125.415 -26.1793) 
(list 3125.415 -26.3563) 
(list 3199.4375 -26.7063)))
(apply 'command (append '("pline") coords '("c")))
(setq currobj (ssadd (entlast) currobj))
(setq coords (list 
(list 3199.4375 -26.8493) 
(list 3125.415 -26.4993) 
(list 3125.415 -26.6763) 
(list 3199.4375 -26.9263)))
(apply 'command (append '("pline") coords '("c")))
(setq currobj (ssadd (entlast) currobj))
(setq coords (list 
(list 3199.4375 -27.0693) 
(list 3125.415 -26.8193) 
(list 3125.415 -26.9963) 
(list 3199.4375 -27.1463)))
(apply 'command (append '("pline") coords '("c")))
(setq currobj (ssadd (entlast) currobj))
(setq coords (list 
(list 3199.4375 -27.2893) 
(list 3125.415 -27.1393) 
(list 3125.415 -27.3163) 
(list 3199.4375 -27.3663)))
(apply 'command (append '("pline") coords '("c")))
(setq currobj (ssadd (entlast) currobj))
(setq coords (list 
(list 3199.4375 -27.5093) 
(list 3125.415 -27.4593) 
(list 3125.415 -27.6363) 
(list 3199.4375 -27.5863)))
(apply 'command (append '("pline") coords '("c")))
(setq currobj (ssadd (entlast) currobj))
(setq coords (list 
(list 3199.4375 -27.7293) 
(list 3125.415 -27.7793) 
(list 3125.415 -27.9563) 
(list 3199.4375 -27.8063)))
(apply 'command (append '("pline") coords '("c")))
(setq currobj (ssadd (entlast) currobj))
(setq coords (list 
(list 3199.4375 -27.9493) 
(list 3125.415 -28.0993) 
(list 3125.415 -28.2763) 
(list 3199.4375 -28.0263)))
(apply 'command (append '("pline") coords '("c")))
(setq currobj (ssadd (entlast) currobj))
(setq coords (list 
(list 3199.4375 -28.1693) 
(list 3125.415 -28.4193) 
(list 3125.415 -28.5963) 
(list 3199.4375 -28.2463)))
(apply 'command (append '("pline") coords '("c")))
(setq currobj (ssadd (entlast) currobj))
(setq coords (list 
(list 3199.4375 -28.3893) 
(list 3125.415 -28.7393) 
(list 3125.415 -28.9163) 
(list 3199.4375 -28.4663)))
(apply 'command (append '("pline") coords '("c")))
(setq currobj (ssadd (entlast) currobj))
(setq coords (list 
(list 3199.4375 -28.6093) 
(list 3125.415 -29.0593) 
(list 3125.415 -29.2363) 
(list 3199.4375 -28.6863)))
(apply 'command (append '("pline") coords '("c")))
(setq currobj (ssadd (entlast) currobj))
(setq coords (list 
(list 3199.4375 -28.8293) 
(list 3125.415 -29.3793) 
(list 3125.415 -29.5563) 
(list 3199.4375 -28.9063)))
(apply 'command (append '("pline") coords '("c")))
(setq currobj (ssadd (entlast) currobj))
(setq coords (list 
(list 3199.4375 -29.0493) 
(list 3125.415 -29.6993) 
(list 3125.415 -29.8763) 
(list 3199.4375 -29.1263)))
(apply 'command (append '("pline") coords '("c")))
(setq currobj (ssadd (entlast) currobj))
(command "_layer" "set" "nitride" "")
(command "_layer" "set" "text" "")
(command "_circle" "3199.0625,-40.2693" "0.075")
(command "_circle" "3199.0625,-39.9693" "0.075")
(command "_circle" "3199.0625,-39.6693" "0.075")
(command "_circle" "3199.0625,-39.3693" "0.075")
(command "_circle" "3199.0625,-39.0693" "0.075")
(command "_circle" "3198.7625,-40.2693" "0.075")
(command "_circle" "3198.7625,-39.9693" "0.075")
(command "_circle" "3198.7625,-39.6693" "0.075")
(command "_circle" "3198.7625,-39.3693" "0.075")
(command "_circle" "3198.7625,-39.0693" "0.075")
(command "_circle" "3198.4625,-40.2693" "0.075")
(command "_circle" "3198.4625,-39.9693" "0.075")
(command "_circle" "3198.4625,-39.6693" "0.075")
(command "_circle" "3198.4625,-39.3693" "0.075")
(command "_circle" "3198.4625,-39.0693" "0.075")
(command "_circle" "3198.1625,-40.2693" "0.075")
(command "_circle" "3198.1625,-39.9693" "0.075")
(command "_circle" "3198.1625,-39.6693" "0.075")
(command "_circle" "3198.1625,-39.3693" "0.075")
(command "_circle" "3198.1625,-39.0693" "0.075")
(command "_circle" "3197.8625,-40.2693" "0.075")
(command "_circle" "3197.8625,-39.9693" "0.075")
(command "_circle" "3197.8625,-39.6693" "0.075")
(command "_circle" "3197.8625,-39.3693" "0.075")
(command "_circle" "3197.8625,-39.0693" "0.075")
(command "_layer" "set" "nitride" "")
(setq coords (list 
(list 3200.2625 -14.8263) 
(list 3200.2625 100.8184) 
(list 3199.7375 100.8184) 
(list 3199.7375 -14.8263)))
(apply 'command (append '("pline") coords '("c")))
(setq currobj (ssadd (entlast) currobj))
(command "_layer" "set" "prebias" "")
(command "_rectangle" "3199.7375,-14.8263" "3200.2625,100.8184")
(setq currobj (ssadd (entlast) currobj))
(command "_layer" "set" "nitride" "")
(setq coords (list 
(list 3200.2625 100.8184) 
(list 3200.5625 110.8184) 
(list 3200.5625 110.8184) 
(list 3200.5625 111.8184) 
(list 3274.585 111.0684) 
(list 3274.585 116.0114) 
(list 3200.5625 115.2614) 
(list 3200.5625 116.2614) 
(list 3200.5625 116.2614) 
(list 3200.2625 126.2614) 
(list 3199.7375 126.2614) 
(list 3199.4375 116.2614) 
(list 3199.4375 116.2614) 
(list 3199.4375 115.2614) 
(list 3125.415 116.0114) 
(list 3125.415 111.0684) 
(list 3199.4375 111.8184) 
(list 3199.4375 110.8184) 
(list 3199.4375 110.8184) 
(list 3199.7375 100.8184)))
(apply 'command (append '("pline") coords '("c")))
(setq currobj (ssadd (entlast) currobj))
(command "_layer" "set" "prebias" "")
(setq coords (list 
(list 3199.4375 100.8184) 
(list 3199.4375 111.8184) 
(list 3125.415 111.0684) 
(list 3125.415 116.0114) 
(list 3199.4375 115.2614) 
(list 3199.4375 126.2614) 
(list 3200.5625 126.2614) 
(list 3200.5625 115.2614) 
(list 3274.585 116.0114) 
(list 3274.585 111.0684) 
(list 3200.5625 111.8184) 
(list 3200.5625 100.8184)))
(apply 'command (append '("pline") coords '("c")))
(setq currobj (ssadd (entlast) currobj))
(command "_layer" "set" "nitride" "")
(command "_layer" "set" "fda1" "")
(setq coords (list 
(list 3200.5625 111.9614) 
(list 3274.585 111.2114) 
(list 3274.585 111.3884) 
(list 3200.5625 112.0384)))
(apply 'command (append '("pline") coords '("c")))
(setq currobj (ssadd (entlast) currobj))
(setq coords (list 
(list 3200.5625 112.1814) 
(list 3274.585 111.5314) 
(list 3274.585 111.7084) 
(list 3200.5625 112.2584)))
(apply 'command (append '("pline") coords '("c")))
(setq currobj (ssadd (entlast) currobj))
(setq coords (list 
(list 3200.5625 112.4014) 
(list 3274.585 111.8514) 
(list 3274.585 112.0284) 
(list 3200.5625 112.4784)))
(apply 'command (append '("pline") coords '("c")))
(setq currobj (ssadd (entlast) currobj))
(setq coords (list 
(list 3200.5625 112.6214) 
(list 3274.585 112.1714) 
(list 3274.585 112.3484) 
(list 3200.5625 112.6984)))
(apply 'command (append '("pline") coords '("c")))
(setq currobj (ssadd (entlast) currobj))
(setq coords (list 
(list 3200.5625 112.8414) 
(list 3274.585 112.4914) 
(list 3274.585 112.6684) 
(list 3200.5625 112.9184)))
(apply 'command (append '("pline") coords '("c")))
(setq currobj (ssadd (entlast) currobj))
(setq coords (list 
(list 3200.5625 113.0614) 
(list 3274.585 112.8114) 
(list 3274.585 112.9884) 
(list 3200.5625 113.1384)))
(apply 'command (append '("pline") coords '("c")))
(setq currobj (ssadd (entlast) currobj))
(setq coords (list 
(list 3200.5625 113.2814) 
(list 3274.585 113.1314) 
(list 3274.585 113.3084) 
(list 3200.5625 113.3584)))
(apply 'command (append '("pline") coords '("c")))
(setq currobj (ssadd (entlast) currobj))
(setq coords (list 
(list 3200.5625 113.5014) 
(list 3274.585 113.4514) 
(list 3274.585 113.6284) 
(list 3200.5625 113.5784)))
(apply 'command (append '("pline") coords '("c")))
(setq currobj (ssadd (entlast) currobj))
(setq coords (list 
(list 3200.5625 113.7214) 
(list 3274.585 113.7714) 
(list 3274.585 113.9484) 
(list 3200.5625 113.7984)))
(apply 'command (append '("pline") coords '("c")))
(setq currobj (ssadd (entlast) currobj))
(setq coords (list 
(list 3200.5625 113.9414) 
(list 3274.585 114.0914) 
(list 3274.585 114.2684) 
(list 3200.5625 114.0184)))
(apply 'command (append '("pline") coords '("c")))
(setq currobj (ssadd (entlast) currobj))
(setq coords (list 
(list 3200.5625 114.1614) 
(list 3274.585 114.4114) 
(list 3274.585 114.5884) 
(list 3200.5625 114.2384)))
(apply 'command (append '("pline") coords '("c")))
(setq currobj (ssadd (entlast) currobj))
(setq coords (list 
(list 3200.5625 114.3814) 
(list 3274.585 114.7314) 
(list 3274.585 114.9084) 
(list 3200.5625 114.4584)))
(apply 'command (append '("pline") coords '("c")))
(setq currobj (ssadd (entlast) currobj))
(setq coords (list 
(list 3200.5625 114.6014) 
(list 3274.585 115.0514) 
(list 3274.585 115.2284) 
(list 3200.5625 114.6784)))
(apply 'command (append '("pline") coords '("c")))
(setq currobj (ssadd (entlast) currobj))
(setq coords (list 
(list 3200.5625 114.8214) 
(list 3274.585 115.3714) 
(list 3274.585 115.5484) 
(list 3200.5625 114.8984)))
(apply 'command (append '("pline") coords '("c")))
(setq currobj (ssadd (entlast) currobj))
(setq coords (list 
(list 3200.5625 115.0414) 
(list 3274.585 115.6914) 
(list 3274.585 115.8684) 
(list 3200.5625 115.1184)))
(apply 'command (append '("pline") coords '("c")))
(setq currobj (ssadd (entlast) currobj))
(setq coords (list 
(list 3199.4375 115.1184) 
(list 3125.415 115.8684) 
(list 3125.415 115.6914) 
(list 3199.4375 115.0414)))
(apply 'command (append '("pline") coords '("c")))
(setq currobj (ssadd (entlast) currobj))
(setq coords (list 
(list 3199.4375 114.8984) 
(list 3125.415 115.5484) 
(list 3125.415 115.3714) 
(list 3199.4375 114.8214)))
(apply 'command (append '("pline") coords '("c")))
(setq currobj (ssadd (entlast) currobj))
(setq coords (list 
(list 3199.4375 114.6784) 
(list 3125.415 115.2284) 
(list 3125.415 115.0514) 
(list 3199.4375 114.6014)))
(apply 'command (append '("pline") coords '("c")))
(setq currobj (ssadd (entlast) currobj))
(setq coords (list 
(list 3199.4375 114.4584) 
(list 3125.415 114.9084) 
(list 3125.415 114.7314) 
(list 3199.4375 114.3814)))
(apply 'command (append '("pline") coords '("c")))
(setq currobj (ssadd (entlast) currobj))
(setq coords (list 
(list 3199.4375 114.2384) 
(list 3125.415 114.5884) 
(list 3125.415 114.4114) 
(list 3199.4375 114.1614)))
(apply 'command (append '("pline") coords '("c")))
(setq currobj (ssadd (entlast) currobj))
(setq coords (list 
(list 3199.4375 114.0184) 
(list 3125.415 114.2684) 
(list 3125.415 114.0914) 
(list 3199.4375 113.9414)))
(apply 'command (append '("pline") coords '("c")))
(setq currobj (ssadd (entlast) currobj))
(setq coords (list 
(list 3199.4375 113.7984) 
(list 3125.415 113.9484) 
(list 3125.415 113.7714) 
(list 3199.4375 113.7214)))
(apply 'command (append '("pline") coords '("c")))
(setq currobj (ssadd (entlast) currobj))
(setq coords (list 
(list 3199.4375 113.5784) 
(list 3125.415 113.6284) 
(list 3125.415 113.4514) 
(list 3199.4375 113.5014)))
(apply 'command (append '("pline") coords '("c")))
(setq currobj (ssadd (entlast) currobj))
(setq coords (list 
(list 3199.4375 113.3584) 
(list 3125.415 113.3084) 
(list 3125.415 113.1314) 
(list 3199.4375 113.2814)))
(apply 'command (append '("pline") coords '("c")))
(setq currobj (ssadd (entlast) currobj))
(setq coords (list 
(list 3199.4375 113.1384) 
(list 3125.415 112.9884) 
(list 3125.415 112.8114) 
(list 3199.4375 113.0614)))
(apply 'command (append '("pline") coords '("c")))
(setq currobj (ssadd (entlast) currobj))
(setq coords (list 
(list 3199.4375 112.9184) 
(list 3125.415 112.6684) 
(list 3125.415 112.4914) 
(list 3199.4375 112.8414)))
(apply 'command (append '("pline") coords '("c")))
(setq currobj (ssadd (entlast) currobj))
(setq coords (list 
(list 3199.4375 112.6984) 
(list 3125.415 112.3484) 
(list 3125.415 112.1714) 
(list 3199.4375 112.6214)))
(apply 'command (append '("pline") coords '("c")))
(setq currobj (ssadd (entlast) currobj))
(setq coords (list 
(list 3199.4375 112.4784) 
(list 3125.415 112.0284) 
(list 3125.415 111.8514) 
(list 3199.4375 112.4014)))
(apply 'command (append '("pline") coords '("c")))
(setq currobj (ssadd (entlast) currobj))
(setq coords (list 
(list 3199.4375 112.2584) 
(list 3125.415 111.7084) 
(list 3125.415 111.5314) 
(list 3199.4375 112.1814)))
(apply 'command (append '("pline") coords '("c")))
(setq currobj (ssadd (entlast) currobj))
(setq coords (list 
(list 3199.4375 112.0384) 
(list 3125.415 111.3884) 
(list 3125.415 111.2114) 
(list 3199.4375 111.9614)))
(apply 'command (append '("pline") coords '("c")))
(setq currobj (ssadd (entlast) currobj))
(command "_layer" "set" "nitride" "")
(command "_layer" "set" "text" "")
(command "_circle" "3199.0625,100.8184" "0.075")
(command "_circle" "3199.0625,101.1184" "0.075")
(command "_circle" "3199.0625,101.4184" "0.075")
(command "_circle" "3199.0625,101.7184" "0.075")
(command "_circle" "3199.0625,102.0184" "0.075")
(command "_circle" "3198.7625,100.8184" "0.075")
(command "_circle" "3198.7625,101.1184" "0.075")
(command "_circle" "3198.7625,101.4184" "0.075")
(command "_circle" "3198.7625,101.7184" "0.075")
(command "_circle" "3198.7625,102.0184" "0.075")
(command "_circle" "3198.4625,100.8184" "0.075")
(command "_circle" "3198.4625,101.1184" "0.075")
(command "_circle" "3198.4625,101.4184" "0.075")
(command "_circle" "3198.4625,101.7184" "0.075")
(command "_circle" "3198.4625,102.0184" "0.075")
(command "_circle" "3198.1625,100.8184" "0.075")
(command "_circle" "3198.1625,101.1184" "0.075")
(command "_circle" "3198.1625,101.4184" "0.075")
(command "_circle" "3198.1625,101.7184" "0.075")
(command "_circle" "3198.1625,102.0184" "0.075")
(command "_circle" "3197.8625,100.8184" "0.075")
(command "_circle" "3197.8625,101.1184" "0.075")
(command "_circle" "3197.8625,101.4184" "0.075")
(command "_circle" "3197.8625,101.7184" "0.075")
(command "_circle" "3197.8625,102.0184" "0.075")
(command "_layer" "set" "nitride" "")
(setq coords (list 
(list 3200.2625 126.2614) 
(list 3200.2625 241.9061) 
(list 3199.7375 241.9061) 
(list 3199.7375 126.2614)))
(apply 'command (append '("pline") coords '("c")))
(setq currobj (ssadd (entlast) currobj))
(command "_layer" "set" "prebias" "")
(command "_rectangle" "3199.7375,126.2614" "3200.2625,241.9061")
(setq currobj (ssadd (entlast) currobj))
(command "_layer" "set" "nitride" "")
(setq coords (list 
(list 3200.2625 241.9061) 
(list 3200.5625 251.9061) 
(list 3200.5625 251.9061) 
(list 3200.5625 252.9061) 
(list 3274.585 252.1561) 
(list 3274.585 257.0991) 
(list 3200.5625 256.3491) 
(list 3200.5625 257.3491) 
(list 3200.5625 257.3491) 
(list 3200.2625 267.3491) 
(list 3199.7375 267.3491) 
(list 3199.4375 257.3491) 
(list 3199.4375 257.3491) 
(list 3199.4375 256.3491) 
(list 3125.415 257.0991) 
(list 3125.415 252.1561) 
(list 3199.4375 252.9061) 
(list 3199.4375 251.9061) 
(list 3199.4375 251.9061) 
(list 3199.7375 241.9061)))
(apply 'command (append '("pline") coords '("c")))
(setq currobj (ssadd (entlast) currobj))
(command "_layer" "set" "prebias" "")
(setq coords (list 
(list 3199.4375 241.9061) 
(list 3199.4375 252.9061) 
(list 3125.415 252.1561) 
(list 3125.415 257.0991) 
(list 3199.4375 256.3491) 
(list 3199.4375 267.3491) 
(list 3200.5625 267.3491) 
(list 3200.5625 256.3491) 
(list 3274.585 257.0991) 
(list 3274.585 252.1561) 
(list 3200.5625 252.9061) 
(list 3200.5625 241.9061)))
(apply 'command (append '("pline") coords '("c")))
(setq currobj (ssadd (entlast) currobj))
(command "_layer" "set" "nitride" "")
(command "_layer" "set" "fda1" "")
(setq coords (list 
(list 3200.5625 253.0491) 
(list 3274.585 252.2991) 
(list 3274.585 252.4761) 
(list 3200.5625 253.1261)))
(apply 'command (append '("pline") coords '("c")))
(setq currobj (ssadd (entlast) currobj))
(setq coords (list 
(list 3200.5625 253.2691) 
(list 3274.585 252.6191) 
(list 3274.585 252.7961) 
(list 3200.5625 253.3461)))
(apply 'command (append '("pline") coords '("c")))
(setq currobj (ssadd (entlast) currobj))
(setq coords (list 
(list 3200.5625 253.4891) 
(list 3274.585 252.9391) 
(list 3274.585 253.1161) 
(list 3200.5625 253.5661)))
(apply 'command (append '("pline") coords '("c")))
(setq currobj (ssadd (entlast) currobj))
(setq coords (list 
(list 3200.5625 253.7091) 
(list 3274.585 253.2591) 
(list 3274.585 253.4361) 
(list 3200.5625 253.7861)))
(apply 'command (append '("pline") coords '("c")))
(setq currobj (ssadd (entlast) currobj))
(setq coords (list 
(list 3200.5625 253.9291) 
(list 3274.585 253.5791) 
(list 3274.585 253.7561) 
(list 3200.5625 254.0061)))
(apply 'command (append '("pline") coords '("c")))
(setq currobj (ssadd (entlast) currobj))
(setq coords (list 
(list 3200.5625 254.1491) 
(list 3274.585 253.8991) 
(list 3274.585 254.0761) 
(list 3200.5625 254.2261)))
(apply 'command (append '("pline") coords '("c")))
(setq currobj (ssadd (entlast) currobj))
(setq coords (list 
(list 3200.5625 254.3691) 
(list 3274.585 254.2191) 
(list 3274.585 254.3961) 
(list 3200.5625 254.4461)))
(apply 'command (append '("pline") coords '("c")))
(setq currobj (ssadd (entlast) currobj))
(setq coords (list 
(list 3200.5625 254.5891) 
(list 3274.585 254.5391) 
(list 3274.585 254.7161) 
(list 3200.5625 254.6661)))
(apply 'command (append '("pline") coords '("c")))
(setq currobj (ssadd (entlast) currobj))
(setq coords (list 
(list 3200.5625 254.8091) 
(list 3274.585 254.8591) 
(list 3274.585 255.0361) 
(list 3200.5625 254.8861)))
(apply 'command (append '("pline") coords '("c")))
(setq currobj (ssadd (entlast) currobj))
(setq coords (list 
(list 3200.5625 255.0291) 
(list 3274.585 255.1791) 
(list 3274.585 255.3561) 
(list 3200.5625 255.1061)))
(apply 'command (append '("pline") coords '("c")))
(setq currobj (ssadd (entlast) currobj))
(setq coords (list 
(list 3200.5625 255.2491) 
(list 3274.585 255.4991) 
(list 3274.585 255.6761) 
(list 3200.5625 255.3261)))
(apply 'command (append '("pline") coords '("c")))
(setq currobj (ssadd (entlast) currobj))
(setq coords (list 
(list 3200.5625 255.4691) 
(list 3274.585 255.8191) 
(list 3274.585 255.9961) 
(list 3200.5625 255.5461)))
(apply 'command (append '("pline") coords '("c")))
(setq currobj (ssadd (entlast) currobj))
(setq coords (list 
(list 3200.5625 255.6891) 
(list 3274.585 256.1391) 
(list 3274.585 256.3161) 
(list 3200.5625 255.7661)))
(apply 'command (append '("pline") coords '("c")))
(setq currobj (ssadd (entlast) currobj))
(setq coords (list 
(list 3200.5625 255.9091) 
(list 3274.585 256.4591) 
(list 3274.585 256.6361) 
(list 3200.5625 255.9861)))
(apply 'command (append '("pline") coords '("c")))
(setq currobj (ssadd (entlast) currobj))
(setq coords (list 
(list 3200.5625 256.1291) 
(list 3274.585 256.7791) 
(list 3274.585 256.9561) 
(list 3200.5625 256.2061)))
(apply 'command (append '("pline") coords '("c")))
(setq currobj (ssadd (entlast) currobj))
(setq coords (list 
(list 3199.4375 256.2061) 
(list 3125.415 256.9561) 
(list 3125.415 256.7791) 
(list 3199.4375 256.1291)))
(apply 'command (append '("pline") coords '("c")))
(setq currobj (ssadd (entlast) currobj))
(setq coords (list 
(list 3199.4375 255.9861) 
(list 3125.415 256.6361) 
(list 3125.415 256.4591) 
(list 3199.4375 255.9091)))
(apply 'command (append '("pline") coords '("c")))
(setq currobj (ssadd (entlast) currobj))
(setq coords (list 
(list 3199.4375 255.7661) 
(list 3125.415 256.3161) 
(list 3125.415 256.1391) 
(list 3199.4375 255.6891)))
(apply 'command (append '("pline") coords '("c")))
(setq currobj (ssadd (entlast) currobj))
(setq coords (list 
(list 3199.4375 255.5461) 
(list 3125.415 255.9961) 
(list 3125.415 255.8191) 
(list 3199.4375 255.4691)))
(apply 'command (append '("pline") coords '("c")))
(setq currobj (ssadd (entlast) currobj))
(setq coords (list 
(list 3199.4375 255.3261) 
(list 3125.415 255.6761) 
(list 3125.415 255.4991) 
(list 3199.4375 255.2491)))
(apply 'command (append '("pline") coords '("c")))
(setq currobj (ssadd (entlast) currobj))
(setq coords (list 
(list 3199.4375 255.1061) 
(list 3125.415 255.3561) 
(list 3125.415 255.1791) 
(list 3199.4375 255.0291)))
(apply 'command (append '("pline") coords '("c")))
(setq currobj (ssadd (entlast) currobj))
(setq coords (list 
(list 3199.4375 254.8861) 
(list 3125.415 255.0361) 
(list 3125.415 254.8591) 
(list 3199.4375 254.8091)))
(apply 'command (append '("pline") coords '("c")))
(setq currobj (ssadd (entlast) currobj))
(setq coords (list 
(list 3199.4375 254.6661) 
(list 3125.415 254.7161) 
(list 3125.415 254.5391) 
(list 3199.4375 254.5891)))
(apply 'command (append '("pline") coords '("c")))
(setq currobj (ssadd (entlast) currobj))
(setq coords (list 
(list 3199.4375 254.4461) 
(list 3125.415 254.3961) 
(list 3125.415 254.2191) 
(list 3199.4375 254.3691)))
(apply 'command (append '("pline") coords '("c")))
(setq currobj (ssadd (entlast) currobj))
(setq coords (list 
(list 3199.4375 254.2261) 
(list 3125.415 254.0761) 
(list 3125.415 253.8991) 
(list 3199.4375 254.1491)))
(apply 'command (append '("pline") coords '("c")))
(setq currobj (ssadd (entlast) currobj))
(setq coords (list 
(list 3199.4375 254.0061) 
(list 3125.415 253.7561) 
(list 3125.415 253.5791) 
(list 3199.4375 253.9291)))
(apply 'command (append '("pline") coords '("c")))
(setq currobj (ssadd (entlast) currobj))
(setq coords (list 
(list 3199.4375 253.7861) 
(list 3125.415 253.4361) 
(list 3125.415 253.2591) 
(list 3199.4375 253.7091)))
(apply 'command (append '("pline") coords '("c")))
(setq currobj (ssadd (entlast) currobj))
(setq coords (list 
(list 3199.4375 253.5661) 
(list 3125.415 253.1161) 
(list 3125.415 252.9391) 
(list 3199.4375 253.4891)))
(apply 'command (append '("pline") coords '("c")))
(setq currobj (ssadd (entlast) currobj))
(setq coords (list 
(list 3199.4375 253.3461) 
(list 3125.415 252.7961) 
(list 3125.415 252.6191) 
(list 3199.4375 253.2691)))
(apply 'command (append '("pline") coords '("c")))
(setq currobj (ssadd (entlast) currobj))
(setq coords (list 
(list 3199.4375 253.1261) 
(list 3125.415 252.4761) 
(list 3125.415 252.2991) 
(list 3199.4375 253.0491)))
(apply 'command (append '("pline") coords '("c")))
(setq currobj (ssadd (entlast) currobj))
(command "_layer" "set" "nitride" "")
(command "_layer" "set" "text" "")
(command "_circle" "3199.0625,241.9061" "0.075")
(command "_circle" "3199.0625,242.2061" "0.075")
(command "_circle" "3199.0625,242.5061" "0.075")
(command "_circle" "3199.0625,242.8061" "0.075")
(command "_circle" "3199.0625,243.1061" "0.075")
(command "_circle" "3198.7625,241.9061" "0.075")
(command "_circle" "3198.7625,242.2061" "0.075")
(command "_circle" "3198.7625,242.5061" "0.075")
(command "_circle" "3198.7625,242.8061" "0.075")
(command "_circle" "3198.7625,243.1061" "0.075")
(command "_circle" "3198.4625,241.9061" "0.075")
(command "_circle" "3198.4625,242.2061" "0.075")
(command "_circle" "3198.4625,242.5061" "0.075")
(command "_circle" "3198.4625,242.8061" "0.075")
(command "_circle" "3198.4625,243.1061" "0.075")
(command "_circle" "3198.1625,241.9061" "0.075")
(command "_circle" "3198.1625,242.2061" "0.075")
(command "_circle" "3198.1625,242.5061" "0.075")
(command "_circle" "3198.1625,242.8061" "0.075")
(command "_circle" "3198.1625,243.1061" "0.075")
(command "_circle" "3197.8625,241.9061" "0.075")
(command "_circle" "3197.8625,242.2061" "0.075")
(command "_circle" "3197.8625,242.5061" "0.075")
(command "_circle" "3197.8625,242.8061" "0.075")
(command "_circle" "3197.8625,243.1061" "0.075")
(command "_layer" "set" "nitride" "")
(setq coords (list 
(list 3200.2625 267.3491) 
(list 3200.2625 382.9939) 
(list 3199.7375 382.9939) 
(list 3199.7375 267.3491)))
(apply 'command (append '("pline") coords '("c")))
(setq currobj (ssadd (entlast) currobj))
(command "_layer" "set" "prebias" "")
(command "_rectangle" "3199.7375,267.3491" "3200.2625,382.9939")
(setq currobj (ssadd (entlast) currobj))
(command "_layer" "set" "nitride" "")
(setq coords (list 
(list 3200.2625 382.9939) 
(list 3200.5625 392.9939) 
(list 3200.5625 392.9939) 
(list 3200.5625 393.9939) 
(list 3274.585 393.2439) 
(list 3274.585 398.1869) 
(list 3200.5625 397.4369) 
(list 3200.5625 398.4369) 
(list 3200.5625 398.4369) 
(list 3200.2625 408.4369) 
(list 3199.7375 408.4369) 
(list 3199.4375 398.4369) 
(list 3199.4375 398.4369) 
(list 3199.4375 397.4369) 
(list 3125.415 398.1869) 
(list 3125.415 393.2439) 
(list 3199.4375 393.9939) 
(list 3199.4375 392.9939) 
(list 3199.4375 392.9939) 
(list 3199.7375 382.9939)))
(apply 'command (append '("pline") coords '("c")))
(setq currobj (ssadd (entlast) currobj))
(command "_layer" "set" "prebias" "")
(setq coords (list 
(list 3199.4375 382.9939) 
(list 3199.4375 393.9939) 
(list 3125.415 393.2439) 
(list 3125.415 398.1869) 
(list 3199.4375 397.4369) 
(list 3199.4375 408.4369) 
(list 3200.5625 408.4369) 
(list 3200.5625 397.4369) 
(list 3274.585 398.1869) 
(list 3274.585 393.2439) 
(list 3200.5625 393.9939) 
(list 3200.5625 382.9939)))
(apply 'command (append '("pline") coords '("c")))
(setq currobj (ssadd (entlast) currobj))
(command "_layer" "set" "nitride" "")
(command "_layer" "set" "fda1" "")
(setq coords (list 
(list 3200.5625 394.1369) 
(list 3274.585 393.3869) 
(list 3274.585 393.5639) 
(list 3200.5625 394.2139)))
(apply 'command (append '("pline") coords '("c")))
(setq currobj (ssadd (entlast) currobj))
(setq coords (list 
(list 3200.5625 394.3569) 
(list 3274.585 393.7069) 
(list 3274.585 393.8839) 
(list 3200.5625 394.4339)))
(apply 'command (append '("pline") coords '("c")))
(setq currobj (ssadd (entlast) currobj))
(setq coords (list 
(list 3200.5625 394.5769) 
(list 3274.585 394.0269) 
(list 3274.585 394.2039) 
(list 3200.5625 394.6539)))
(apply 'command (append '("pline") coords '("c")))
(setq currobj (ssadd (entlast) currobj))
(setq coords (list 
(list 3200.5625 394.7969) 
(list 3274.585 394.3469) 
(list 3274.585 394.5239) 
(list 3200.5625 394.8739)))
(apply 'command (append '("pline") coords '("c")))
(setq currobj (ssadd (entlast) currobj))
(setq coords (list 
(list 3200.5625 395.0169) 
(list 3274.585 394.6669) 
(list 3274.585 394.8439) 
(list 3200.5625 395.0939)))
(apply 'command (append '("pline") coords '("c")))
(setq currobj (ssadd (entlast) currobj))
(setq coords (list 
(list 3200.5625 395.2369) 
(list 3274.585 394.9869) 
(list 3274.585 395.1639) 
(list 3200.5625 395.3139)))
(apply 'command (append '("pline") coords '("c")))
(setq currobj (ssadd (entlast) currobj))
(setq coords (list 
(list 3200.5625 395.4569) 
(list 3274.585 395.3069) 
(list 3274.585 395.4839) 
(list 3200.5625 395.5339)))
(apply 'command (append '("pline") coords '("c")))
(setq currobj (ssadd (entlast) currobj))
(setq coords (list 
(list 3200.5625 395.6769) 
(list 3274.585 395.6269) 
(list 3274.585 395.8039) 
(list 3200.5625 395.7539)))
(apply 'command (append '("pline") coords '("c")))
(setq currobj (ssadd (entlast) currobj))
(setq coords (list 
(list 3200.5625 395.8969) 
(list 3274.585 395.9469) 
(list 3274.585 396.1239) 
(list 3200.5625 395.9739)))
(apply 'command (append '("pline") coords '("c")))
(setq currobj (ssadd (entlast) currobj))
(setq coords (list 
(list 3200.5625 396.1169) 
(list 3274.585 396.2669) 
(list 3274.585 396.4439) 
(list 3200.5625 396.1939)))
(apply 'command (append '("pline") coords '("c")))
(setq currobj (ssadd (entlast) currobj))
(setq coords (list 
(list 3200.5625 396.3369) 
(list 3274.585 396.5869) 
(list 3274.585 396.7639) 
(list 3200.5625 396.4139)))
(apply 'command (append '("pline") coords '("c")))
(setq currobj (ssadd (entlast) currobj))
(setq coords (list 
(list 3200.5625 396.5569) 
(list 3274.585 396.9069) 
(list 3274.585 397.0839) 
(list 3200.5625 396.6339)))
(apply 'command (append '("pline") coords '("c")))
(setq currobj (ssadd (entlast) currobj))
(setq coords (list 
(list 3200.5625 396.7769) 
(list 3274.585 397.2269) 
(list 3274.585 397.4039) 
(list 3200.5625 396.8539)))
(apply 'command (append '("pline") coords '("c")))
(setq currobj (ssadd (entlast) currobj))
(setq coords (list 
(list 3200.5625 396.9969) 
(list 3274.585 397.5469) 
(list 3274.585 397.7239) 
(list 3200.5625 397.0739)))
(apply 'command (append '("pline") coords '("c")))
(setq currobj (ssadd (entlast) currobj))
(setq coords (list 
(list 3200.5625 397.2169) 
(list 3274.585 397.8669) 
(list 3274.585 398.0439) 
(list 3200.5625 397.2939)))
(apply 'command (append '("pline") coords '("c")))
(setq currobj (ssadd (entlast) currobj))
(setq coords (list 
(list 3199.4375 397.2939) 
(list 3125.415 398.0439) 
(list 3125.415 397.8669) 
(list 3199.4375 397.2169)))
(apply 'command (append '("pline") coords '("c")))
(setq currobj (ssadd (entlast) currobj))
(setq coords (list 
(list 3199.4375 397.0739) 
(list 3125.415 397.7239) 
(list 3125.415 397.5469) 
(list 3199.4375 396.9969)))
(apply 'command (append '("pline") coords '("c")))
(setq currobj (ssadd (entlast) currobj))
(setq coords (list 
(list 3199.4375 396.8539) 
(list 3125.415 397.4039) 
(list 3125.415 397.2269) 
(list 3199.4375 396.7769)))
(apply 'command (append '("pline") coords '("c")))
(setq currobj (ssadd (entlast) currobj))
(setq coords (list 
(list 3199.4375 396.6339) 
(list 3125.415 397.0839) 
(list 3125.415 396.9069) 
(list 3199.4375 396.5569)))
(apply 'command (append '("pline") coords '("c")))
(setq currobj (ssadd (entlast) currobj))
(setq coords (list 
(list 3199.4375 396.4139) 
(list 3125.415 396.7639) 
(list 3125.415 396.5869) 
(list 3199.4375 396.3369)))
(apply 'command (append '("pline") coords '("c")))
(setq currobj (ssadd (entlast) currobj))
(setq coords (list 
(list 3199.4375 396.1939) 
(list 3125.415 396.4439) 
(list 3125.415 396.2669) 
(list 3199.4375 396.1169)))
(apply 'command (append '("pline") coords '("c")))
(setq currobj (ssadd (entlast) currobj))
(setq coords (list 
(list 3199.4375 395.9739) 
(list 3125.415 396.1239) 
(list 3125.415 395.9469) 
(list 3199.4375 395.8969)))
(apply 'command (append '("pline") coords '("c")))
(setq currobj (ssadd (entlast) currobj))
(setq coords (list 
(list 3199.4375 395.7539) 
(list 3125.415 395.8039) 
(list 3125.415 395.6269) 
(list 3199.4375 395.6769)))
(apply 'command (append '("pline") coords '("c")))
(setq currobj (ssadd (entlast) currobj))
(setq coords (list 
(list 3199.4375 395.5339) 
(list 3125.415 395.4839) 
(list 3125.415 395.3069) 
(list 3199.4375 395.4569)))
(apply 'command (append '("pline") coords '("c")))
(setq currobj (ssadd (entlast) currobj))
(setq coords (list 
(list 3199.4375 395.3139) 
(list 3125.415 395.1639) 
(list 3125.415 394.9869) 
(list 3199.4375 395.2369)))
(apply 'command (append '("pline") coords '("c")))
(setq currobj (ssadd (entlast) currobj))
(setq coords (list 
(list 3199.4375 395.0939) 
(list 3125.415 394.8439) 
(list 3125.415 394.6669) 
(list 3199.4375 395.0169)))
(apply 'command (append '("pline") coords '("c")))
(setq currobj (ssadd (entlast) currobj))
(setq coords (list 
(list 3199.4375 394.8739) 
(list 3125.415 394.5239) 
(list 3125.415 394.3469) 
(list 3199.4375 394.7969)))
(apply 'command (append '("pline") coords '("c")))
(setq currobj (ssadd (entlast) currobj))
(setq coords (list 
(list 3199.4375 394.6539) 
(list 3125.415 394.2039) 
(list 3125.415 394.0269) 
(list 3199.4375 394.5769)))
(apply 'command (append '("pline") coords '("c")))
(setq currobj (ssadd (entlast) currobj))
(setq coords (list 
(list 3199.4375 394.4339) 
(list 3125.415 393.8839) 
(list 3125.415 393.7069) 
(list 3199.4375 394.3569)))
(apply 'command (append '("pline") coords '("c")))
(setq currobj (ssadd (entlast) currobj))
(setq coords (list 
(list 3199.4375 394.2139) 
(list 3125.415 393.5639) 
(list 3125.415 393.3869) 
(list 3199.4375 394.1369)))
(apply 'command (append '("pline") coords '("c")))
(setq currobj (ssadd (entlast) currobj))
(command "_layer" "set" "nitride" "")
(command "_layer" "set" "text" "")
(command "_circle" "3199.0625,382.9939" "0.075")
(command "_circle" "3199.0625,383.2939" "0.075")
(command "_circle" "3199.0625,383.5939" "0.075")
(command "_circle" "3199.0625,383.8939" "0.075")
(command "_circle" "3199.0625,384.1939" "0.075")
(command "_circle" "3198.7625,382.9939" "0.075")
(command "_circle" "3198.7625,383.2939" "0.075")
(command "_circle" "3198.7625,383.5939" "0.075")
(command "_circle" "3198.7625,383.8939" "0.075")
(command "_circle" "3198.7625,384.1939" "0.075")
(command "_circle" "3198.4625,382.9939" "0.075")
(command "_circle" "3198.4625,383.2939" "0.075")
(command "_circle" "3198.4625,383.5939" "0.075")
(command "_circle" "3198.4625,383.8939" "0.075")
(command "_circle" "3198.4625,384.1939" "0.075")
(command "_circle" "3198.1625,382.9939" "0.075")
(command "_circle" "3198.1625,383.2939" "0.075")
(command "_circle" "3198.1625,383.5939" "0.075")
(command "_circle" "3198.1625,383.8939" "0.075")
(command "_circle" "3198.1625,384.1939" "0.075")
(command "_circle" "3197.8625,382.9939" "0.075")
(command "_circle" "3197.8625,383.2939" "0.075")
(command "_circle" "3197.8625,383.5939" "0.075")
(command "_circle" "3197.8625,383.8939" "0.075")
(command "_circle" "3197.8625,384.1939" "0.075")
(command "_layer" "set" "nitride" "")
(setq coords (list 
(list 3200.2625 408.4369) 
(list 3200.2625 524.0816) 
(list 3199.7375 524.0816) 
(list 3199.7375 408.4369)))
(apply 'command (append '("pline") coords '("c")))
(setq currobj (ssadd (entlast) currobj))
(command "_layer" "set" "prebias" "")
(command "_rectangle" "3199.7375,408.4369" "3200.2625,524.0816")
(setq currobj (ssadd (entlast) currobj))
(command "_layer" "set" "nitride" "")
(setq coords (list 
(list 3200.2625 524.0816) 
(list 3200.5625 534.0816) 
(list 3200.5625 534.0816) 
(list 3200.5625 535.0816) 
(list 3274.585 534.3316) 
(list 3274.585 539.2746) 
(list 3200.5625 538.5246) 
(list 3200.5625 539.5246) 
(list 3200.5625 539.5246) 
(list 3200.2625 549.5246) 
(list 3199.7375 549.5246) 
(list 3199.4375 539.5246) 
(list 3199.4375 539.5246) 
(list 3199.4375 538.5246) 
(list 3125.415 539.2746) 
(list 3125.415 534.3316) 
(list 3199.4375 535.0816) 
(list 3199.4375 534.0816) 
(list 3199.4375 534.0816) 
(list 3199.7375 524.0816)))
(apply 'command (append '("pline") coords '("c")))
(setq currobj (ssadd (entlast) currobj))
(command "_layer" "set" "prebias" "")
(setq coords (list 
(list 3199.4375 524.0816) 
(list 3199.4375 535.0816) 
(list 3125.415 534.3316) 
(list 3125.415 539.2746) 
(list 3199.4375 538.5246) 
(list 3199.4375 549.5246) 
(list 3200.5625 549.5246) 
(list 3200.5625 538.5246) 
(list 3274.585 539.2746) 
(list 3274.585 534.3316) 
(list 3200.5625 535.0816) 
(list 3200.5625 524.0816)))
(apply 'command (append '("pline") coords '("c")))
(setq currobj (ssadd (entlast) currobj))
(command "_layer" "set" "nitride" "")
(command "_layer" "set" "fda1" "")
(setq coords (list 
(list 3200.5625 535.2246) 
(list 3274.585 534.4746) 
(list 3274.585 534.6516) 
(list 3200.5625 535.3016)))
(apply 'command (append '("pline") coords '("c")))
(setq currobj (ssadd (entlast) currobj))
(setq coords (list 
(list 3200.5625 535.4446) 
(list 3274.585 534.7946) 
(list 3274.585 534.9716) 
(list 3200.5625 535.5216)))
(apply 'command (append '("pline") coords '("c")))
(setq currobj (ssadd (entlast) currobj))
(setq coords (list 
(list 3200.5625 535.6646) 
(list 3274.585 535.1146) 
(list 3274.585 535.2916) 
(list 3200.5625 535.7416)))
(apply 'command (append '("pline") coords '("c")))
(setq currobj (ssadd (entlast) currobj))
(setq coords (list 
(list 3200.5625 535.8846) 
(list 3274.585 535.4346) 
(list 3274.585 535.6116) 
(list 3200.5625 535.9616)))
(apply 'command (append '("pline") coords '("c")))
(setq currobj (ssadd (entlast) currobj))
(setq coords (list 
(list 3200.5625 536.1046) 
(list 3274.585 535.7546) 
(list 3274.585 535.9316) 
(list 3200.5625 536.1816)))
(apply 'command (append '("pline") coords '("c")))
(setq currobj (ssadd (entlast) currobj))
(setq coords (list 
(list 3200.5625 536.3246) 
(list 3274.585 536.0746) 
(list 3274.585 536.2516) 
(list 3200.5625 536.4016)))
(apply 'command (append '("pline") coords '("c")))
(setq currobj (ssadd (entlast) currobj))
(setq coords (list 
(list 3200.5625 536.5446) 
(list 3274.585 536.3946) 
(list 3274.585 536.5716) 
(list 3200.5625 536.6216)))
(apply 'command (append '("pline") coords '("c")))
(setq currobj (ssadd (entlast) currobj))
(setq coords (list 
(list 3200.5625 536.7646) 
(list 3274.585 536.7146) 
(list 3274.585 536.8916) 
(list 3200.5625 536.8416)))
(apply 'command (append '("pline") coords '("c")))
(setq currobj (ssadd (entlast) currobj))
(setq coords (list 
(list 3200.5625 536.9846) 
(list 3274.585 537.0346) 
(list 3274.585 537.2116) 
(list 3200.5625 537.0616)))
(apply 'command (append '("pline") coords '("c")))
(setq currobj (ssadd (entlast) currobj))
(setq coords (list 
(list 3200.5625 537.2046) 
(list 3274.585 537.3546) 
(list 3274.585 537.5316) 
(list 3200.5625 537.2816)))
(apply 'command (append '("pline") coords '("c")))
(setq currobj (ssadd (entlast) currobj))
(setq coords (list 
(list 3200.5625 537.4246) 
(list 3274.585 537.6746) 
(list 3274.585 537.8516) 
(list 3200.5625 537.5016)))
(apply 'command (append '("pline") coords '("c")))
(setq currobj (ssadd (entlast) currobj))
(setq coords (list 
(list 3200.5625 537.6446) 
(list 3274.585 537.9946) 
(list 3274.585 538.1716) 
(list 3200.5625 537.7216)))
(apply 'command (append '("pline") coords '("c")))
(setq currobj (ssadd (entlast) currobj))
(setq coords (list 
(list 3200.5625 537.8646) 
(list 3274.585 538.3146) 
(list 3274.585 538.4916) 
(list 3200.5625 537.9416)))
(apply 'command (append '("pline") coords '("c")))
(setq currobj (ssadd (entlast) currobj))
(setq coords (list 
(list 3200.5625 538.0846) 
(list 3274.585 538.6346) 
(list 3274.585 538.8116) 
(list 3200.5625 538.1616)))
(apply 'command (append '("pline") coords '("c")))
(setq currobj (ssadd (entlast) currobj))
(setq coords (list 
(list 3200.5625 538.3046) 
(list 3274.585 538.9546) 
(list 3274.585 539.1316) 
(list 3200.5625 538.3816)))
(apply 'command (append '("pline") coords '("c")))
(setq currobj (ssadd (entlast) currobj))
(setq coords (list 
(list 3199.4375 538.3816) 
(list 3125.415 539.1316) 
(list 3125.415 538.9546) 
(list 3199.4375 538.3046)))
(apply 'command (append '("pline") coords '("c")))
(setq currobj (ssadd (entlast) currobj))
(setq coords (list 
(list 3199.4375 538.1616) 
(list 3125.415 538.8116) 
(list 3125.415 538.6346) 
(list 3199.4375 538.0846)))
(apply 'command (append '("pline") coords '("c")))
(setq currobj (ssadd (entlast) currobj))
(setq coords (list 
(list 3199.4375 537.9416) 
(list 3125.415 538.4916) 
(list 3125.415 538.3146) 
(list 3199.4375 537.8646)))
(apply 'command (append '("pline") coords '("c")))
(setq currobj (ssadd (entlast) currobj))
(setq coords (list 
(list 3199.4375 537.7216) 
(list 3125.415 538.1716) 
(list 3125.415 537.9946) 
(list 3199.4375 537.6446)))
(apply 'command (append '("pline") coords '("c")))
(setq currobj (ssadd (entlast) currobj))
(setq coords (list 
(list 3199.4375 537.5016) 
(list 3125.415 537.8516) 
(list 3125.415 537.6746) 
(list 3199.4375 537.4246)))
(apply 'command (append '("pline") coords '("c")))
(setq currobj (ssadd (entlast) currobj))
(setq coords (list 
(list 3199.4375 537.2816) 
(list 3125.415 537.5316) 
(list 3125.415 537.3546) 
(list 3199.4375 537.2046)))
(apply 'command (append '("pline") coords '("c")))
(setq currobj (ssadd (entlast) currobj))
(setq coords (list 
(list 3199.4375 537.0616) 
(list 3125.415 537.2116) 
(list 3125.415 537.0346) 
(list 3199.4375 536.9846)))
(apply 'command (append '("pline") coords '("c")))
(setq currobj (ssadd (entlast) currobj))
(setq coords (list 
(list 3199.4375 536.8416) 
(list 3125.415 536.8916) 
(list 3125.415 536.7146) 
(list 3199.4375 536.7646)))
(apply 'command (append '("pline") coords '("c")))
(setq currobj (ssadd (entlast) currobj))
(setq coords (list 
(list 3199.4375 536.6216) 
(list 3125.415 536.5716) 
(list 3125.415 536.3946) 
(list 3199.4375 536.5446)))
(apply 'command (append '("pline") coords '("c")))
(setq currobj (ssadd (entlast) currobj))
(setq coords (list 
(list 3199.4375 536.4016) 
(list 3125.415 536.2516) 
(list 3125.415 536.0746) 
(list 3199.4375 536.3246)))
(apply 'command (append '("pline") coords '("c")))
(setq currobj (ssadd (entlast) currobj))
(setq coords (list 
(list 3199.4375 536.1816) 
(list 3125.415 535.9316) 
(list 3125.415 535.7546) 
(list 3199.4375 536.1046)))
(apply 'command (append '("pline") coords '("c")))
(setq currobj (ssadd (entlast) currobj))
(setq coords (list 
(list 3199.4375 535.9616) 
(list 3125.415 535.6116) 
(list 3125.415 535.4346) 
(list 3199.4375 535.8846)))
(apply 'command (append '("pline") coords '("c")))
(setq currobj (ssadd (entlast) currobj))
(setq coords (list 
(list 3199.4375 535.7416) 
(list 3125.415 535.2916) 
(list 3125.415 535.1146) 
(list 3199.4375 535.6646)))
(apply 'command (append '("pline") coords '("c")))
(setq currobj (ssadd (entlast) currobj))
(setq coords (list 
(list 3199.4375 535.5216) 
(list 3125.415 534.9716) 
(list 3125.415 534.7946) 
(list 3199.4375 535.4446)))
(apply 'command (append '("pline") coords '("c")))
(setq currobj (ssadd (entlast) currobj))
(setq coords (list 
(list 3199.4375 535.3016) 
(list 3125.415 534.6516) 
(list 3125.415 534.4746) 
(list 3199.4375 535.2246)))
(apply 'command (append '("pline") coords '("c")))
(setq currobj (ssadd (entlast) currobj))
(command "_layer" "set" "nitride" "")
(command "_layer" "set" "text" "")
(command "_circle" "3199.0625,524.0816" "0.075")
(command "_circle" "3199.0625,524.3816" "0.075")
(command "_circle" "3199.0625,524.6816" "0.075")
(command "_circle" "3199.0625,524.9816" "0.075")
(command "_circle" "3199.0625,525.2816" "0.075")
(command "_circle" "3198.7625,524.0816" "0.075")
(command "_circle" "3198.7625,524.3816" "0.075")
(command "_circle" "3198.7625,524.6816" "0.075")
(command "_circle" "3198.7625,524.9816" "0.075")
(command "_circle" "3198.7625,525.2816" "0.075")
(command "_circle" "3198.4625,524.0816" "0.075")
(command "_circle" "3198.4625,524.3816" "0.075")
(command "_circle" "3198.4625,524.6816" "0.075")
(command "_circle" "3198.4625,524.9816" "0.075")
(command "_circle" "3198.4625,525.2816" "0.075")
(command "_circle" "3198.1625,524.0816" "0.075")
(command "_circle" "3198.1625,524.3816" "0.075")
(command "_circle" "3198.1625,524.6816" "0.075")
(command "_circle" "3198.1625,524.9816" "0.075")
(command "_circle" "3198.1625,525.2816" "0.075")
(command "_circle" "3197.8625,524.0816" "0.075")
(command "_circle" "3197.8625,524.3816" "0.075")
(command "_circle" "3197.8625,524.6816" "0.075")
(command "_circle" "3197.8625,524.9816" "0.075")
(command "_circle" "3197.8625,525.2816" "0.075")
(command "_layer" "set" "nitride" "")
(setq coords (list 
(list 3200.2625 549.5246) 
(list 3200.2625 665.1693) 
(list 3199.7375 665.1693) 
(list 3199.7375 549.5246)))
(apply 'command (append '("pline") coords '("c")))
(setq currobj (ssadd (entlast) currobj))
(command "_layer" "set" "prebias" "")
(command "_rectangle" "3199.7375,549.5246" "3200.2625,665.1693")
(setq currobj (ssadd (entlast) currobj))
(command "_layer" "set" "nitride" "")
(setq coords (list 
(list 3200.2625 665.1693) 
(list 3200.5625 675.1693) 
(list 3200.5625 675.1693) 
(list 3200.5625 676.1693) 
(list 3274.585 675.4193) 
(list 3274.585 680.3623) 
(list 3200.5625 679.6123) 
(list 3200.5625 680.6123) 
(list 3200.5625 680.6123) 
(list 3200.2625 690.6123) 
(list 3199.7375 690.6123) 
(list 3199.4375 680.6123) 
(list 3199.4375 680.6123) 
(list 3199.4375 679.6123) 
(list 3125.415 680.3623) 
(list 3125.415 675.4193) 
(list 3199.4375 676.1693) 
(list 3199.4375 675.1693) 
(list 3199.4375 675.1693) 
(list 3199.7375 665.1693)))
(apply 'command (append '("pline") coords '("c")))
(setq currobj (ssadd (entlast) currobj))
(command "_layer" "set" "prebias" "")
(setq coords (list 
(list 3199.4375 665.1693) 
(list 3199.4375 676.1693) 
(list 3125.415 675.4193) 
(list 3125.415 680.3623) 
(list 3199.4375 679.6123) 
(list 3199.4375 690.6123) 
(list 3200.5625 690.6123) 
(list 3200.5625 679.6123) 
(list 3274.585 680.3623) 
(list 3274.585 675.4193) 
(list 3200.5625 676.1693) 
(list 3200.5625 665.1693)))
(apply 'command (append '("pline") coords '("c")))
(setq currobj (ssadd (entlast) currobj))
(command "_layer" "set" "nitride" "")
(command "_layer" "set" "fda1" "")
(setq coords (list 
(list 3200.5625 676.3123) 
(list 3274.585 675.5623) 
(list 3274.585 675.7393) 
(list 3200.5625 676.3893)))
(apply 'command (append '("pline") coords '("c")))
(setq currobj (ssadd (entlast) currobj))
(setq coords (list 
(list 3200.5625 676.5323) 
(list 3274.585 675.8823) 
(list 3274.585 676.0593) 
(list 3200.5625 676.6093)))
(apply 'command (append '("pline") coords '("c")))
(setq currobj (ssadd (entlast) currobj))
(setq coords (list 
(list 3200.5625 676.7523) 
(list 3274.585 676.2023) 
(list 3274.585 676.3793) 
(list 3200.5625 676.8293)))
(apply 'command (append '("pline") coords '("c")))
(setq currobj (ssadd (entlast) currobj))
(setq coords (list 
(list 3200.5625 676.9723) 
(list 3274.585 676.5223) 
(list 3274.585 676.6993) 
(list 3200.5625 677.0493)))
(apply 'command (append '("pline") coords '("c")))
(setq currobj (ssadd (entlast) currobj))
(setq coords (list 
(list 3200.5625 677.1923) 
(list 3274.585 676.8423) 
(list 3274.585 677.0193) 
(list 3200.5625 677.2693)))
(apply 'command (append '("pline") coords '("c")))
(setq currobj (ssadd (entlast) currobj))
(setq coords (list 
(list 3200.5625 677.4123) 
(list 3274.585 677.1623) 
(list 3274.585 677.3393) 
(list 3200.5625 677.4893)))
(apply 'command (append '("pline") coords '("c")))
(setq currobj (ssadd (entlast) currobj))
(setq coords (list 
(list 3200.5625 677.6323) 
(list 3274.585 677.4823) 
(list 3274.585 677.6593) 
(list 3200.5625 677.7093)))
(apply 'command (append '("pline") coords '("c")))
(setq currobj (ssadd (entlast) currobj))
(setq coords (list 
(list 3200.5625 677.8523) 
(list 3274.585 677.8023) 
(list 3274.585 677.9793) 
(list 3200.5625 677.9293)))
(apply 'command (append '("pline") coords '("c")))
(setq currobj (ssadd (entlast) currobj))
(setq coords (list 
(list 3200.5625 678.0723) 
(list 3274.585 678.1223) 
(list 3274.585 678.2993) 
(list 3200.5625 678.1493)))
(apply 'command (append '("pline") coords '("c")))
(setq currobj (ssadd (entlast) currobj))
(setq coords (list 
(list 3200.5625 678.2923) 
(list 3274.585 678.4423) 
(list 3274.585 678.6193) 
(list 3200.5625 678.3693)))
(apply 'command (append '("pline") coords '("c")))
(setq currobj (ssadd (entlast) currobj))
(setq coords (list 
(list 3200.5625 678.5123) 
(list 3274.585 678.7623) 
(list 3274.585 678.9393) 
(list 3200.5625 678.5893)))
(apply 'command (append '("pline") coords '("c")))
(setq currobj (ssadd (entlast) currobj))
(setq coords (list 
(list 3200.5625 678.7323) 
(list 3274.585 679.0823) 
(list 3274.585 679.2593) 
(list 3200.5625 678.8093)))
(apply 'command (append '("pline") coords '("c")))
(setq currobj (ssadd (entlast) currobj))
(setq coords (list 
(list 3200.5625 678.9523) 
(list 3274.585 679.4023) 
(list 3274.585 679.5793) 
(list 3200.5625 679.0293)))
(apply 'command (append '("pline") coords '("c")))
(setq currobj (ssadd (entlast) currobj))
(setq coords (list 
(list 3200.5625 679.1723) 
(list 3274.585 679.7223) 
(list 3274.585 679.8993) 
(list 3200.5625 679.2493)))
(apply 'command (append '("pline") coords '("c")))
(setq currobj (ssadd (entlast) currobj))
(setq coords (list 
(list 3200.5625 679.3923) 
(list 3274.585 680.0423) 
(list 3274.585 680.2193) 
(list 3200.5625 679.4693)))
(apply 'command (append '("pline") coords '("c")))
(setq currobj (ssadd (entlast) currobj))
(setq coords (list 
(list 3199.4375 679.4693) 
(list 3125.415 680.2193) 
(list 3125.415 680.0423) 
(list 3199.4375 679.3923)))
(apply 'command (append '("pline") coords '("c")))
(setq currobj (ssadd (entlast) currobj))
(setq coords (list 
(list 3199.4375 679.2493) 
(list 3125.415 679.8993) 
(list 3125.415 679.7223) 
(list 3199.4375 679.1723)))
(apply 'command (append '("pline") coords '("c")))
(setq currobj (ssadd (entlast) currobj))
(setq coords (list 
(list 3199.4375 679.0293) 
(list 3125.415 679.5793) 
(list 3125.415 679.4023) 
(list 3199.4375 678.9523)))
(apply 'command (append '("pline") coords '("c")))
(setq currobj (ssadd (entlast) currobj))
(setq coords (list 
(list 3199.4375 678.8093) 
(list 3125.415 679.2593) 
(list 3125.415 679.0823) 
(list 3199.4375 678.7323)))
(apply 'command (append '("pline") coords '("c")))
(setq currobj (ssadd (entlast) currobj))
(setq coords (list 
(list 3199.4375 678.5893) 
(list 3125.415 678.9393) 
(list 3125.415 678.7623) 
(list 3199.4375 678.5123)))
(apply 'command (append '("pline") coords '("c")))
(setq currobj (ssadd (entlast) currobj))
(setq coords (list 
(list 3199.4375 678.3693) 
(list 3125.415 678.6193) 
(list 3125.415 678.4423) 
(list 3199.4375 678.2923)))
(apply 'command (append '("pline") coords '("c")))
(setq currobj (ssadd (entlast) currobj))
(setq coords (list 
(list 3199.4375 678.1493) 
(list 3125.415 678.2993) 
(list 3125.415 678.1223) 
(list 3199.4375 678.0723)))
(apply 'command (append '("pline") coords '("c")))
(setq currobj (ssadd (entlast) currobj))
(setq coords (list 
(list 3199.4375 677.9293) 
(list 3125.415 677.9793) 
(list 3125.415 677.8023) 
(list 3199.4375 677.8523)))
(apply 'command (append '("pline") coords '("c")))
(setq currobj (ssadd (entlast) currobj))
(setq coords (list 
(list 3199.4375 677.7093) 
(list 3125.415 677.6593) 
(list 3125.415 677.4823) 
(list 3199.4375 677.6323)))
(apply 'command (append '("pline") coords '("c")))
(setq currobj (ssadd (entlast) currobj))
(setq coords (list 
(list 3199.4375 677.4893) 
(list 3125.415 677.3393) 
(list 3125.415 677.1623) 
(list 3199.4375 677.4123)))
(apply 'command (append '("pline") coords '("c")))
(setq currobj (ssadd (entlast) currobj))
(setq coords (list 
(list 3199.4375 677.2693) 
(list 3125.415 677.0193) 
(list 3125.415 676.8423) 
(list 3199.4375 677.1923)))
(apply 'command (append '("pline") coords '("c")))
(setq currobj (ssadd (entlast) currobj))
(setq coords (list 
(list 3199.4375 677.0493) 
(list 3125.415 676.6993) 
(list 3125.415 676.5223) 
(list 3199.4375 676.9723)))
(apply 'command (append '("pline") coords '("c")))
(setq currobj (ssadd (entlast) currobj))
(setq coords (list 
(list 3199.4375 676.8293) 
(list 3125.415 676.3793) 
(list 3125.415 676.2023) 
(list 3199.4375 676.7523)))
(apply 'command (append '("pline") coords '("c")))
(setq currobj (ssadd (entlast) currobj))
(setq coords (list 
(list 3199.4375 676.6093) 
(list 3125.415 676.0593) 
(list 3125.415 675.8823) 
(list 3199.4375 676.5323)))
(apply 'command (append '("pline") coords '("c")))
(setq currobj (ssadd (entlast) currobj))
(setq coords (list 
(list 3199.4375 676.3893) 
(list 3125.415 675.7393) 
(list 3125.415 675.5623) 
(list 3199.4375 676.3123)))
(apply 'command (append '("pline") coords '("c")))
(setq currobj (ssadd (entlast) currobj))
(command "_layer" "set" "nitride" "")
(command "_layer" "set" "text" "")
(command "_circle" "3199.0625,665.1693" "0.075")
(command "_circle" "3199.0625,665.4693" "0.075")
(command "_circle" "3199.0625,665.7693" "0.075")
(command "_circle" "3199.0625,666.0693" "0.075")
(command "_circle" "3199.0625,666.3693" "0.075")
(command "_circle" "3198.7625,665.1693" "0.075")
(command "_circle" "3198.7625,665.4693" "0.075")
(command "_circle" "3198.7625,665.7693" "0.075")
(command "_circle" "3198.7625,666.0693" "0.075")
(command "_circle" "3198.7625,666.3693" "0.075")
(command "_circle" "3198.4625,665.1693" "0.075")
(command "_circle" "3198.4625,665.4693" "0.075")
(command "_circle" "3198.4625,665.7693" "0.075")
(command "_circle" "3198.4625,666.0693" "0.075")
(command "_circle" "3198.4625,666.3693" "0.075")
(command "_circle" "3198.1625,665.1693" "0.075")
(command "_circle" "3198.1625,665.4693" "0.075")
(command "_circle" "3198.1625,665.7693" "0.075")
(command "_circle" "3198.1625,666.0693" "0.075")
(command "_circle" "3198.1625,666.3693" "0.075")
(command "_circle" "3197.8625,665.1693" "0.075")
(command "_circle" "3197.8625,665.4693" "0.075")
(command "_circle" "3197.8625,665.7693" "0.075")
(command "_circle" "3197.8625,666.0693" "0.075")
(command "_circle" "3197.8625,666.3693" "0.075")
(command "_layer" "set" "nitride" "")
(setq coords (list 
(list 3200.2625 690.6123) 
(list 3200.2625 806.257) 
(list 3199.7375 806.257) 
(list 3199.7375 690.6123)))
(apply 'command (append '("pline") coords '("c")))
(setq currobj (ssadd (entlast) currobj))
(command "_layer" "set" "prebias" "")
(command "_rectangle" "3199.7375,690.6123" "3200.2625,806.257")
(setq currobj (ssadd (entlast) currobj))
(command "_layer" "set" "nitride" "")
(setq coords (list 
(list 3200.2625 806.257) 
(list 3200.5625 816.257) 
(list 3200.5625 816.257) 
(list 3200.5625 817.257) 
(list 3274.585 816.507) 
(list 3274.585 821.45) 
(list 3200.5625 820.7) 
(list 3200.5625 821.7) 
(list 3200.5625 821.7) 
(list 3200.2625 831.7) 
(list 3199.7375 831.7) 
(list 3199.4375 821.7) 
(list 3199.4375 821.7) 
(list 3199.4375 820.7) 
(list 3125.415 821.45) 
(list 3125.415 816.507) 
(list 3199.4375 817.257) 
(list 3199.4375 816.257) 
(list 3199.4375 816.257) 
(list 3199.7375 806.257)))
(apply 'command (append '("pline") coords '("c")))
(setq currobj (ssadd (entlast) currobj))
(command "_layer" "set" "prebias" "")
(setq coords (list 
(list 3199.4375 806.257) 
(list 3199.4375 817.257) 
(list 3125.415 816.507) 
(list 3125.415 821.45) 
(list 3199.4375 820.7) 
(list 3199.4375 831.7) 
(list 3200.5625 831.7) 
(list 3200.5625 820.7) 
(list 3274.585 821.45) 
(list 3274.585 816.507) 
(list 3200.5625 817.257) 
(list 3200.5625 806.257)))
(apply 'command (append '("pline") coords '("c")))
(setq currobj (ssadd (entlast) currobj))
(command "_layer" "set" "nitride" "")
(command "_layer" "set" "fda1" "")
(setq coords (list 
(list 3200.5625 817.4) 
(list 3274.585 816.65) 
(list 3274.585 816.827) 
(list 3200.5625 817.477)))
(apply 'command (append '("pline") coords '("c")))
(setq currobj (ssadd (entlast) currobj))
(setq coords (list 
(list 3200.5625 817.62) 
(list 3274.585 816.97) 
(list 3274.585 817.147) 
(list 3200.5625 817.697)))
(apply 'command (append '("pline") coords '("c")))
(setq currobj (ssadd (entlast) currobj))
(setq coords (list 
(list 3200.5625 817.84) 
(list 3274.585 817.29) 
(list 3274.585 817.467) 
(list 3200.5625 817.917)))
(apply 'command (append '("pline") coords '("c")))
(setq currobj (ssadd (entlast) currobj))
(setq coords (list 
(list 3200.5625 818.06) 
(list 3274.585 817.61) 
(list 3274.585 817.787) 
(list 3200.5625 818.137)))
(apply 'command (append '("pline") coords '("c")))
(setq currobj (ssadd (entlast) currobj))
(setq coords (list 
(list 3200.5625 818.28) 
(list 3274.585 817.93) 
(list 3274.585 818.107) 
(list 3200.5625 818.357)))
(apply 'command (append '("pline") coords '("c")))
(setq currobj (ssadd (entlast) currobj))
(setq coords (list 
(list 3200.5625 818.5) 
(list 3274.585 818.25) 
(list 3274.585 818.427) 
(list 3200.5625 818.577)))
(apply 'command (append '("pline") coords '("c")))
(setq currobj (ssadd (entlast) currobj))
(setq coords (list 
(list 3200.5625 818.72) 
(list 3274.585 818.57) 
(list 3274.585 818.747) 
(list 3200.5625 818.797)))
(apply 'command (append '("pline") coords '("c")))
(setq currobj (ssadd (entlast) currobj))
(setq coords (list 
(list 3200.5625 818.94) 
(list 3274.585 818.89) 
(list 3274.585 819.067) 
(list 3200.5625 819.017)))
(apply 'command (append '("pline") coords '("c")))
(setq currobj (ssadd (entlast) currobj))
(setq coords (list 
(list 3200.5625 819.16) 
(list 3274.585 819.21) 
(list 3274.585 819.387) 
(list 3200.5625 819.237)))
(apply 'command (append '("pline") coords '("c")))
(setq currobj (ssadd (entlast) currobj))
(setq coords (list 
(list 3200.5625 819.38) 
(list 3274.585 819.53) 
(list 3274.585 819.707) 
(list 3200.5625 819.457)))
(apply 'command (append '("pline") coords '("c")))
(setq currobj (ssadd (entlast) currobj))
(setq coords (list 
(list 3200.5625 819.6) 
(list 3274.585 819.85) 
(list 3274.585 820.027) 
(list 3200.5625 819.677)))
(apply 'command (append '("pline") coords '("c")))
(setq currobj (ssadd (entlast) currobj))
(setq coords (list 
(list 3200.5625 819.82) 
(list 3274.585 820.17) 
(list 3274.585 820.347) 
(list 3200.5625 819.897)))
(apply 'command (append '("pline") coords '("c")))
(setq currobj (ssadd (entlast) currobj))
(setq coords (list 
(list 3200.5625 820.04) 
(list 3274.585 820.49) 
(list 3274.585 820.667) 
(list 3200.5625 820.117)))
(apply 'command (append '("pline") coords '("c")))
(setq currobj (ssadd (entlast) currobj))
(setq coords (list 
(list 3200.5625 820.26) 
(list 3274.585 820.81) 
(list 3274.585 820.987) 
(list 3200.5625 820.337)))
(apply 'command (append '("pline") coords '("c")))
(setq currobj (ssadd (entlast) currobj))
(setq coords (list 
(list 3200.5625 820.48) 
(list 3274.585 821.13) 
(list 3274.585 821.307) 
(list 3200.5625 820.557)))
(apply 'command (append '("pline") coords '("c")))
(setq currobj (ssadd (entlast) currobj))
(setq coords (list 
(list 3199.4375 820.557) 
(list 3125.415 821.307) 
(list 3125.415 821.13) 
(list 3199.4375 820.48)))
(apply 'command (append '("pline") coords '("c")))
(setq currobj (ssadd (entlast) currobj))
(setq coords (list 
(list 3199.4375 820.337) 
(list 3125.415 820.987) 
(list 3125.415 820.81) 
(list 3199.4375 820.26)))
(apply 'command (append '("pline") coords '("c")))
(setq currobj (ssadd (entlast) currobj))
(setq coords (list 
(list 3199.4375 820.117) 
(list 3125.415 820.667) 
(list 3125.415 820.49) 
(list 3199.4375 820.04)))
(apply 'command (append '("pline") coords '("c")))
(setq currobj (ssadd (entlast) currobj))
(setq coords (list 
(list 3199.4375 819.897) 
(list 3125.415 820.347) 
(list 3125.415 820.17) 
(list 3199.4375 819.82)))
(apply 'command (append '("pline") coords '("c")))
(setq currobj (ssadd (entlast) currobj))
(setq coords (list 
(list 3199.4375 819.677) 
(list 3125.415 820.027) 
(list 3125.415 819.85) 
(list 3199.4375 819.6)))
(apply 'command (append '("pline") coords '("c")))
(setq currobj (ssadd (entlast) currobj))
(setq coords (list 
(list 3199.4375 819.457) 
(list 3125.415 819.707) 
(list 3125.415 819.53) 
(list 3199.4375 819.38)))
(apply 'command (append '("pline") coords '("c")))
(setq currobj (ssadd (entlast) currobj))
(setq coords (list 
(list 3199.4375 819.237) 
(list 3125.415 819.387) 
(list 3125.415 819.21) 
(list 3199.4375 819.16)))
(apply 'command (append '("pline") coords '("c")))
(setq currobj (ssadd (entlast) currobj))
(setq coords (list 
(list 3199.4375 819.017) 
(list 3125.415 819.067) 
(list 3125.415 818.89) 
(list 3199.4375 818.94)))
(apply 'command (append '("pline") coords '("c")))
(setq currobj (ssadd (entlast) currobj))
(setq coords (list 
(list 3199.4375 818.797) 
(list 3125.415 818.747) 
(list 3125.415 818.57) 
(list 3199.4375 818.72)))
(apply 'command (append '("pline") coords '("c")))
(setq currobj (ssadd (entlast) currobj))
(setq coords (list 
(list 3199.4375 818.577) 
(list 3125.415 818.427) 
(list 3125.415 818.25) 
(list 3199.4375 818.5)))
(apply 'command (append '("pline") coords '("c")))
(setq currobj (ssadd (entlast) currobj))
(setq coords (list 
(list 3199.4375 818.357) 
(list 3125.415 818.107) 
(list 3125.415 817.93) 
(list 3199.4375 818.28)))
(apply 'command (append '("pline") coords '("c")))
(setq currobj (ssadd (entlast) currobj))
(setq coords (list 
(list 3199.4375 818.137) 
(list 3125.415 817.787) 
(list 3125.415 817.61) 
(list 3199.4375 818.06)))
(apply 'command (append '("pline") coords '("c")))
(setq currobj (ssadd (entlast) currobj))
(setq coords (list 
(list 3199.4375 817.917) 
(list 3125.415 817.467) 
(list 3125.415 817.29) 
(list 3199.4375 817.84)))
(apply 'command (append '("pline") coords '("c")))
(setq currobj (ssadd (entlast) currobj))
(setq coords (list 
(list 3199.4375 817.697) 
(list 3125.415 817.147) 
(list 3125.415 816.97) 
(list 3199.4375 817.62)))
(apply 'command (append '("pline") coords '("c")))
(setq currobj (ssadd (entlast) currobj))
(setq coords (list 
(list 3199.4375 817.477) 
(list 3125.415 816.827) 
(list 3125.415 816.65) 
(list 3199.4375 817.4)))
(apply 'command (append '("pline") coords '("c")))
(setq currobj (ssadd (entlast) currobj))
(command "_layer" "set" "nitride" "")
(command "_layer" "set" "text" "")
(command "_circle" "3199.0625,806.257" "0.075")
(command "_circle" "3199.0625,806.557" "0.075")
(command "_circle" "3199.0625,806.857" "0.075")
(command "_circle" "3199.0625,807.157" "0.075")
(command "_circle" "3199.0625,807.457" "0.075")
(command "_circle" "3198.7625,806.257" "0.075")
(command "_circle" "3198.7625,806.557" "0.075")
(command "_circle" "3198.7625,806.857" "0.075")
(command "_circle" "3198.7625,807.157" "0.075")
(command "_circle" "3198.7625,807.457" "0.075")
(command "_circle" "3198.4625,806.257" "0.075")
(command "_circle" "3198.4625,806.557" "0.075")
(command "_circle" "3198.4625,806.857" "0.075")
(command "_circle" "3198.4625,807.157" "0.075")
(command "_circle" "3198.4625,807.457" "0.075")
(command "_circle" "3198.1625,806.257" "0.075")
(command "_circle" "3198.1625,806.557" "0.075")
(command "_circle" "3198.1625,806.857" "0.075")
(command "_circle" "3198.1625,807.157" "0.075")
(command "_circle" "3198.1625,807.457" "0.075")
(command "_circle" "3197.8625,806.257" "0.075")
(command "_circle" "3197.8625,806.557" "0.075")
(command "_circle" "3197.8625,806.857" "0.075")
(command "_circle" "3197.8625,807.157" "0.075")
(command "_circle" "3197.8625,807.457" "0.075")
(command "_layer" "set" "nitride" "")
(setq coords (list 
(list 3200.2625 831.7) 
(list 3200.2625 836.7) 
(list 3199.7375 836.7) 
(list 3199.7375 831.7)))
(apply 'command (append '("pline") coords '("c")))
(setq currobj (ssadd (entlast) currobj))
(command "_layer" "set" "prebias" "")
(command "_rectangle" "3199.7375,831.7" "3200.2625,836.7")
(setq currobj (ssadd (entlast) currobj))
(command "_layer" "set" "nitride" "")
(setq cooledsinglenanobeam10 currobj)
(setq currobj nil)
(setq currobj (ssadd))
; DRAWING PHOTONIC CRYSTAL
(command "_layer" "set" "negYjunc" "")
(setq coords (list 
(list 3200.135 866.7) 
(list 3200 851.7) 
(list 3200 866.7)))
(apply 'command (append '("pline") coords '("c")))
(setq currobj (ssadd (entlast) currobj))
(setq coords (list 
(list 3200.2625 836.7) 
(list 3200.415 866.7) 
(list 3201.096 866.7) 
(list 3201.096 836.7)))
(apply 'command (append '("pline") coords '("c")))
(setq currobj (ssadd (entlast) currobj))
(setq coords (list 
(list 3199.865 866.7) 
(list 3200 851.7) 
(list 3200 866.7)))
(apply 'command (append '("pline") coords '("c")))
(setq currobj (ssadd (entlast) currobj))
(setq coords (list 
(list 3199.7375 836.7) 
(list 3199.585 866.7) 
(list 3198.904 866.7) 
(list 3198.904 836.7)))
(apply 'command (append '("pline") coords '("c")))
(setq currobj (ssadd (entlast) currobj))
(command "_layer" "set" "nitride" "")
(setq yjunction10 currobj)
(setq currobj nil)
(setq currobj (ssadd))
(setq tap10 nil)
(setq tap10 (ssadd))
(command "_layer" "set" "phc" "")
(setq coords (list 
(list 3200 866.7) 
(list 3200.135 866.7) 
(list 3200.135 866.7103) 
(list 3200.135 866.7206) 
(list 3200.135 866.7308) 
(list 3200.135 866.7411) 
(list 3200.135 866.7514) 
(list 3200.135 866.7617) 
(list 3200.135 866.7719) 
(list 3200.135 866.7822) 
(list 3200.135 866.7925) 
(list 3200.135 866.8028) 
(list 3200.135 866.8131) 
(list 3200.135 866.8233) 
(list 3200.135 866.8336) 
(list 3200.135 866.8439) 
(list 3200.135 866.8542) 
(list 3200.135 866.8644) 
(list 3200.135 866.8747) 
(list 3200.135 866.885) 
(list 3200.135 866.8953) 
(list 3200.135 866.9056) 
(list 3200.135 866.9158) 
(list 3200.135 866.9261) 
(list 3200.135 866.9364) 
(list 3200.135 866.9467) 
(list 3200.135 866.9569) 
(list 3200.135 866.9672) 
(list 3200.135 866.9775) 
(list 3200.135 866.9878) 
(list 3200.135 866.9981) 
(list 3200.135 867.0083) 
(list 3200.135 867.0186) 
(list 3200.135 867.0289) 
(list 3200.135 867.0392) 
(list 3200.135 867.0494) 
(list 3200.135 867.0597) 
(list 3200.135 867.07) 
(list 3200 867.07)))
(apply 'command (append '("pline") coords '("c")))
(setq tap10 (ssadd (entlast) tap10))
(command "_mirror" (entlast) "" "3200,900" "3200,901" "No")
(setq tap10 (ssadd (entlast) tap10))
(setq coords (list 
(list 3200.4239 866.7) 
(list 3200.415 866.7) 
(list 3200.4152 866.7103) 
(list 3200.4155 866.7206) 
(list 3200.4156 866.7308) 
(list 3200.4158 866.7411) 
(list 3200.4158 866.7514) 
(list 3200.4158 866.7617) 
(list 3200.4156 866.7719) 
(list 3200.4154 866.7822) 
(list 3200.4151 866.7925) 
(list 3200.4147 866.8028) 
(list 3200.4142 866.8131) 
(list 3200.4137 866.8233) 
(list 3200.4132 866.8336) 
(list 3200.4126 866.8439) 
(list 3200.4121 866.8542) 
(list 3200.4116 866.8644) 
(list 3200.4113 866.8747) 
(list 3200.411 866.885) 
(list 3200.4108 866.8953) 
(list 3200.4108 866.9056) 
(list 3200.411 866.9158) 
(list 3200.4113 866.9261) 
(list 3200.4118 866.9364) 
(list 3200.4124 866.9467) 
(list 3200.4133 866.9569) 
(list 3200.4142 866.9672) 
(list 3200.4153 866.9775) 
(list 3200.4165 866.9878) 
(list 3200.4177 866.9981) 
(list 3200.4189 867.0083) 
(list 3200.42 867.0186) 
(list 3200.4211 867.0289) 
(list 3200.4221 867.0392) 
(list 3200.4229 867.0494) 
(list 3200.4235 867.0597) 
(list 3200.4239 867.07) 
(list 3200.4239 867.07)))
(apply 'command (append '("pline") coords '("c")))
(setq tap10 (ssadd (entlast) tap10))
(command "_mirror" (entlast) "" "3200,900" "3200,901" "No")
(setq tap10 (ssadd (entlast) tap10))
(setq coords (list 
(list 3201.096 866.7) 
(list 3200.4239 866.7) 
(list 3200.4239 866.7103) 
(list 3200.4239 866.7206) 
(list 3200.4239 866.7308) 
(list 3200.4239 866.7411) 
(list 3200.4239 866.7514) 
(list 3200.4239 866.7617) 
(list 3200.4239 866.7719) 
(list 3200.4239 866.7822) 
(list 3200.4239 866.7925) 
(list 3200.4239 866.8028) 
(list 3200.4239 866.8131) 
(list 3200.4239 866.8233) 
(list 3200.4239 866.8336) 
(list 3200.4239 866.8439) 
(list 3200.4239 866.8542) 
(list 3200.4239 866.8644) 
(list 3200.4239 866.8747) 
(list 3200.4239 866.885) 
(list 3200.4239 866.8953) 
(list 3200.4239 866.9056) 
(list 3200.4239 866.9158) 
(list 3200.4239 866.9261) 
(list 3200.4239 866.9364) 
(list 3200.4239 866.9467) 
(list 3200.4239 866.9569) 
(list 3200.4239 866.9672) 
(list 3200.4239 866.9775) 
(list 3200.4239 866.9878) 
(list 3200.4239 866.9981) 
(list 3200.4239 867.0083) 
(list 3200.4239 867.0186) 
(list 3200.4239 867.0289) 
(list 3200.4239 867.0392) 
(list 3200.4239 867.0494) 
(list 3200.4239 867.0597) 
(list 3200.4239 867.07) 
(list 3201.096 867.07)))
(apply 'command (append '("pline") coords '("c")))
(setq tap10 (ssadd (entlast) tap10))
(command "_mirror" (entlast) "" "3200,900" "3200,901" "No")
(setq tap10 (ssadd (entlast) tap10))
(setq coords (list 
(list 3200 867.07) 
(list 3200.135 867.07) 
(list 3200.135 867.0803) 
(list 3200.135 867.0906) 
(list 3200.135 867.1008) 
(list 3200.135 867.1111) 
(list 3200.135 867.1214) 
(list 3200.135 867.1317) 
(list 3200.135 867.1419) 
(list 3200.135 867.1522) 
(list 3200.135 867.1625) 
(list 3200.135 867.1728) 
(list 3200.135 867.1831) 
(list 3200.135 867.1933) 
(list 3200.135 867.2036) 
(list 3200.135 867.2139) 
(list 3200.135 867.2242) 
(list 3200.135 867.2344) 
(list 3200.135 867.2447) 
(list 3200.135 867.255) 
(list 3200.135 867.2653) 
(list 3200.135 867.2756) 
(list 3200.135 867.2858) 
(list 3200.135 867.2961) 
(list 3200.135 867.3064) 
(list 3200.135 867.3167) 
(list 3200.135 867.3269) 
(list 3200.135 867.3372) 
(list 3200.135 867.3475) 
(list 3200.135 867.3578) 
(list 3200.135 867.3681) 
(list 3200.135 867.3783) 
(list 3200.135 867.3886) 
(list 3200.135 867.3989) 
(list 3200.135 867.4092) 
(list 3200.135 867.4194) 
(list 3200.135 867.4297) 
(list 3200.135 867.44) 
(list 3200 867.44)))
(apply 'command (append '("pline") coords '("c")))
(setq tap10 (ssadd (entlast) tap10))
(command "_mirror" (entlast) "" "3200,900" "3200,901" "No")
(setq tap10 (ssadd (entlast) tap10))
(setq coords (list 
(list 3200.4327 867.07) 
(list 3200.4239 867.07) 
(list 3200.424 867.0803) 
(list 3200.4238 867.0906) 
(list 3200.4234 867.1008) 
(list 3200.4227 867.1111) 
(list 3200.4217 867.1214) 
(list 3200.4204 867.1317) 
(list 3200.4189 867.1419) 
(list 3200.4173 867.1522) 
(list 3200.4155 867.1625) 
(list 3200.4136 867.1728) 
(list 3200.4117 867.1831) 
(list 3200.4099 867.1933) 
(list 3200.4081 867.2036) 
(list 3200.4065 867.2139) 
(list 3200.4052 867.2242) 
(list 3200.4041 867.2344) 
(list 3200.4033 867.2447) 
(list 3200.4029 867.255) 
(list 3200.4029 867.2653) 
(list 3200.4032 867.2756) 
(list 3200.404 867.2858) 
(list 3200.4052 867.2961) 
(list 3200.4067 867.3064) 
(list 3200.4086 867.3167) 
(list 3200.4108 867.3269) 
(list 3200.4132 867.3372) 
(list 3200.4157 867.3475) 
(list 3200.4183 867.3578) 
(list 3200.421 867.3681) 
(list 3200.4235 867.3783) 
(list 3200.4259 867.3886) 
(list 3200.428 867.3989) 
(list 3200.4298 867.4092) 
(list 3200.4312 867.4194) 
(list 3200.4322 867.4297) 
(list 3200.4327 867.44) 
(list 3200.4327 867.44)))
(apply 'command (append '("pline") coords '("c")))
(setq tap10 (ssadd (entlast) tap10))
(command "_mirror" (entlast) "" "3200,900" "3200,901" "No")
(setq tap10 (ssadd (entlast) tap10))
(setq coords (list 
(list 3201.096 867.07) 
(list 3200.4327 867.07) 
(list 3200.4327 867.0803) 
(list 3200.4327 867.0906) 
(list 3200.4327 867.1008) 
(list 3200.4327 867.1111) 
(list 3200.4327 867.1214) 
(list 3200.4327 867.1317) 
(list 3200.4327 867.1419) 
(list 3200.4327 867.1522) 
(list 3200.4327 867.1625) 
(list 3200.4327 867.1728) 
(list 3200.4327 867.1831) 
(list 3200.4327 867.1933) 
(list 3200.4327 867.2036) 
(list 3200.4327 867.2139) 
(list 3200.4327 867.2242) 
(list 3200.4327 867.2344) 
(list 3200.4327 867.2447) 
(list 3200.4327 867.255) 
(list 3200.4327 867.2653) 
(list 3200.4327 867.2756) 
(list 3200.4327 867.2858) 
(list 3200.4327 867.2961) 
(list 3200.4327 867.3064) 
(list 3200.4327 867.3167) 
(list 3200.4327 867.3269) 
(list 3200.4327 867.3372) 
(list 3200.4327 867.3475) 
(list 3200.4327 867.3578) 
(list 3200.4327 867.3681) 
(list 3200.4327 867.3783) 
(list 3200.4327 867.3886) 
(list 3200.4327 867.3989) 
(list 3200.4327 867.4092) 
(list 3200.4327 867.4194) 
(list 3200.4327 867.4297) 
(list 3200.4327 867.44) 
(list 3201.096 867.44)))
(apply 'command (append '("pline") coords '("c")))
(setq tap10 (ssadd (entlast) tap10))
(command "_mirror" (entlast) "" "3200,900" "3200,901" "No")
(setq tap10 (ssadd (entlast) tap10))
(setq coords (list 
(list 3200 867.44) 
(list 3200.135 867.44) 
(list 3200.135 867.4503) 
(list 3200.135 867.4606) 
(list 3200.135 867.4708) 
(list 3200.135 867.4811) 
(list 3200.135 867.4914) 
(list 3200.135 867.5017) 
(list 3200.135 867.5119) 
(list 3200.135 867.5222) 
(list 3200.135 867.5325) 
(list 3200.135 867.5428) 
(list 3200.135 867.5531) 
(list 3200.135 867.5633) 
(list 3200.135 867.5736) 
(list 3200.135 867.5839) 
(list 3200.135 867.5942) 
(list 3200.135 867.6044) 
(list 3200.135 867.6147) 
(list 3200.135 867.625) 
(list 3200.135 867.6353) 
(list 3200.135 867.6456) 
(list 3200.135 867.6558) 
(list 3200.135 867.6661) 
(list 3200.135 867.6764) 
(list 3200.135 867.6867) 
(list 3200.135 867.6969) 
(list 3200.135 867.7072) 
(list 3200.135 867.7175) 
(list 3200.135 867.7278) 
(list 3200.135 867.7381) 
(list 3200.135 867.7483) 
(list 3200.135 867.7586) 
(list 3200.135 867.7689) 
(list 3200.135 867.7792) 
(list 3200.135 867.7894) 
(list 3200.135 867.7997) 
(list 3200.135 867.81) 
(list 3200 867.81)))
(apply 'command (append '("pline") coords '("c")))
(setq tap10 (ssadd (entlast) tap10))
(command "_mirror" (entlast) "" "3200,900" "3200,901" "No")
(setq tap10 (ssadd (entlast) tap10))
(setq coords (list 
(list 3200.4416 867.44) 
(list 3200.4327 867.44) 
(list 3200.4327 867.4503) 
(list 3200.4322 867.4606) 
(list 3200.4311 867.4708) 
(list 3200.4295 867.4811) 
(list 3200.4275 867.4914) 
(list 3200.425 867.5017) 
(list 3200.4222 867.5119) 
(list 3200.4192 867.5222) 
(list 3200.4159 867.5325) 
(list 3200.4126 867.5428) 
(list 3200.4092 867.5531) 
(list 3200.4061 867.5633) 
(list 3200.4031 867.5736) 
(list 3200.4005 867.5839) 
(list 3200.3982 867.5942) 
(list 3200.3965 867.6044) 
(list 3200.3954 867.6147) 
(list 3200.3948 867.625) 
(list 3200.3949 867.6353) 
(list 3200.3957 867.6456) 
(list 3200.3971 867.6558) 
(list 3200.3991 867.6661) 
(list 3200.4017 867.6764) 
(list 3200.4048 867.6867) 
(list 3200.4083 867.6969) 
(list 3200.4121 867.7072) 
(list 3200.4161 867.7175) 
(list 3200.4202 867.7278) 
(list 3200.4242 867.7381) 
(list 3200.4281 867.7483) 
(list 3200.4317 867.7586) 
(list 3200.4349 867.7689) 
(list 3200.4376 867.7792) 
(list 3200.4396 867.7894) 
(list 3200.441 867.7997) 
(list 3200.4416 867.81) 
(list 3200.4416 867.81)))
(apply 'command (append '("pline") coords '("c")))
(setq tap10 (ssadd (entlast) tap10))
(command "_mirror" (entlast) "" "3200,900" "3200,901" "No")
(setq tap10 (ssadd (entlast) tap10))
(setq coords (list 
(list 3201.096 867.44) 
(list 3200.4416 867.44) 
(list 3200.4416 867.4503) 
(list 3200.4416 867.4606) 
(list 3200.4416 867.4708) 
(list 3200.4416 867.4811) 
(list 3200.4416 867.4914) 
(list 3200.4416 867.5017) 
(list 3200.4416 867.5119) 
(list 3200.4416 867.5222) 
(list 3200.4416 867.5325) 
(list 3200.4416 867.5428) 
(list 3200.4416 867.5531) 
(list 3200.4416 867.5633) 
(list 3200.4416 867.5736) 
(list 3200.4416 867.5839) 
(list 3200.4416 867.5942) 
(list 3200.4416 867.6044) 
(list 3200.4416 867.6147) 
(list 3200.4416 867.625) 
(list 3200.4416 867.6353) 
(list 3200.4416 867.6456) 
(list 3200.4416 867.6558) 
(list 3200.4416 867.6661) 
(list 3200.4416 867.6764) 
(list 3200.4416 867.6867) 
(list 3200.4416 867.6969) 
(list 3200.4416 867.7072) 
(list 3200.4416 867.7175) 
(list 3200.4416 867.7278) 
(list 3200.4416 867.7381) 
(list 3200.4416 867.7483) 
(list 3200.4416 867.7586) 
(list 3200.4416 867.7689) 
(list 3200.4416 867.7792) 
(list 3200.4416 867.7894) 
(list 3200.4416 867.7997) 
(list 3200.4416 867.81) 
(list 3201.096 867.81)))
(apply 'command (append '("pline") coords '("c")))
(setq tap10 (ssadd (entlast) tap10))
(command "_mirror" (entlast) "" "3200,900" "3200,901" "No")
(setq tap10 (ssadd (entlast) tap10))
(setq coords (list 
(list 3200 867.81) 
(list 3200.135 867.81) 
(list 3200.135 867.8203) 
(list 3200.135 867.8306) 
(list 3200.135 867.8408) 
(list 3200.135 867.8511) 
(list 3200.135 867.8614) 
(list 3200.135 867.8717) 
(list 3200.135 867.8819) 
(list 3200.135 867.8922) 
(list 3200.135 867.9025) 
(list 3200.135 867.9128) 
(list 3200.135 867.9231) 
(list 3200.135 867.9333) 
(list 3200.135 867.9436) 
(list 3200.135 867.9539) 
(list 3200.135 867.9642) 
(list 3200.135 867.9744) 
(list 3200.135 867.9847) 
(list 3200.135 867.995) 
(list 3200.135 868.0053) 
(list 3200.135 868.0156) 
(list 3200.135 868.0258) 
(list 3200.135 868.0361) 
(list 3200.135 868.0464) 
(list 3200.135 868.0567) 
(list 3200.135 868.0669) 
(list 3200.135 868.0772) 
(list 3200.135 868.0875) 
(list 3200.135 868.0978) 
(list 3200.135 868.1081) 
(list 3200.135 868.1183) 
(list 3200.135 868.1286) 
(list 3200.135 868.1389) 
(list 3200.135 868.1492) 
(list 3200.135 868.1594) 
(list 3200.135 868.1697) 
(list 3200.135 868.18) 
(list 3200 868.18)))
(apply 'command (append '("pline") coords '("c")))
(setq tap10 (ssadd (entlast) tap10))
(command "_mirror" (entlast) "" "3200,900" "3200,901" "No")
(setq tap10 (ssadd (entlast) tap10))
(setq coords (list 
(list 3200.4505 867.81) 
(list 3200.4416 867.81) 
(list 3200.4415 867.8203) 
(list 3200.4405 867.8306) 
(list 3200.4388 867.8408) 
(list 3200.4364 867.8511) 
(list 3200.4333 867.8614) 
(list 3200.4297 867.8717) 
(list 3200.4255 867.8819) 
(list 3200.421 867.8922) 
(list 3200.4163 867.9025) 
(list 3200.4115 867.9128) 
(list 3200.4068 867.9231) 
(list 3200.4022 867.9333) 
(list 3200.3981 867.9436) 
(list 3200.3944 867.9539) 
(list 3200.3913 867.9642) 
(list 3200.389 867.9744) 
(list 3200.3874 867.9847) 
(list 3200.3868 867.995) 
(list 3200.387 868.0053) 
(list 3200.3881 868.0156) 
(list 3200.3902 868.0258) 
(list 3200.393 868.0361) 
(list 3200.3967 868.0464) 
(list 3200.4009 868.0567) 
(list 3200.4058 868.0669) 
(list 3200.411 868.0772) 
(list 3200.4165 868.0875) 
(list 3200.4221 868.0978) 
(list 3200.4275 868.1081) 
(list 3200.4328 868.1183) 
(list 3200.4376 868.1286) 
(list 3200.4418 868.1389) 
(list 3200.4453 868.1492) 
(list 3200.448 868.1594) 
(list 3200.4497 868.1697) 
(list 3200.4505 868.18) 
(list 3200.4505 868.18)))
(apply 'command (append '("pline") coords '("c")))
(setq tap10 (ssadd (entlast) tap10))
(command "_mirror" (entlast) "" "3200,900" "3200,901" "No")
(setq tap10 (ssadd (entlast) tap10))
(setq coords (list 
(list 3201.096 867.81) 
(list 3200.4505 867.81) 
(list 3200.4505 867.8203) 
(list 3200.4505 867.8306) 
(list 3200.4505 867.8408) 
(list 3200.4505 867.8511) 
(list 3200.4505 867.8614) 
(list 3200.4505 867.8717) 
(list 3200.4505 867.8819) 
(list 3200.4505 867.8922) 
(list 3200.4505 867.9025) 
(list 3200.4505 867.9128) 
(list 3200.4505 867.9231) 
(list 3200.4505 867.9333) 
(list 3200.4505 867.9436) 
(list 3200.4505 867.9539) 
(list 3200.4505 867.9642) 
(list 3200.4505 867.9744) 
(list 3200.4505 867.9847) 
(list 3200.4505 867.995) 
(list 3200.4505 868.0053) 
(list 3200.4505 868.0156) 
(list 3200.4505 868.0258) 
(list 3200.4505 868.0361) 
(list 3200.4505 868.0464) 
(list 3200.4505 868.0567) 
(list 3200.4505 868.0669) 
(list 3200.4505 868.0772) 
(list 3200.4505 868.0875) 
(list 3200.4505 868.0978) 
(list 3200.4505 868.1081) 
(list 3200.4505 868.1183) 
(list 3200.4505 868.1286) 
(list 3200.4505 868.1389) 
(list 3200.4505 868.1492) 
(list 3200.4505 868.1594) 
(list 3200.4505 868.1697) 
(list 3200.4505 868.18) 
(list 3201.096 868.18)))
(apply 'command (append '("pline") coords '("c")))
(setq tap10 (ssadd (entlast) tap10))
(command "_mirror" (entlast) "" "3200,900" "3200,901" "No")
(setq tap10 (ssadd (entlast) tap10))
(setq coords (list 
(list 3200 868.18) 
(list 3200.135 868.18) 
(list 3200.135 868.1903) 
(list 3200.135 868.2006) 
(list 3200.135 868.2108) 
(list 3200.135 868.2211) 
(list 3200.135 868.2314) 
(list 3200.135 868.2417) 
(list 3200.135 868.2519) 
(list 3200.135 868.2622) 
(list 3200.135 868.2725) 
(list 3200.135 868.2828) 
(list 3200.135 868.2931) 
(list 3200.135 868.3033) 
(list 3200.135 868.3136) 
(list 3200.135 868.3239) 
(list 3200.135 868.3342) 
(list 3200.135 868.3444) 
(list 3200.135 868.3547) 
(list 3200.135 868.365) 
(list 3200.135 868.3753) 
(list 3200.135 868.3856) 
(list 3200.135 868.3958) 
(list 3200.135 868.4061) 
(list 3200.135 868.4164) 
(list 3200.135 868.4267) 
(list 3200.135 868.4369) 
(list 3200.135 868.4472) 
(list 3200.135 868.4575) 
(list 3200.135 868.4678) 
(list 3200.135 868.4781) 
(list 3200.135 868.4883) 
(list 3200.135 868.4986) 
(list 3200.135 868.5089) 
(list 3200.135 868.5192) 
(list 3200.135 868.5294) 
(list 3200.135 868.5397) 
(list 3200.135 868.55) 
(list 3200 868.55)))
(apply 'command (append '("pline") coords '("c")))
(setq tap10 (ssadd (entlast) tap10))
(command "_mirror" (entlast) "" "3200,900" "3200,901" "No")
(setq tap10 (ssadd (entlast) tap10))
(setq coords (list 
(list 3200.4593 868.18) 
(list 3200.4505 868.18) 
(list 3200.4502 868.1903) 
(list 3200.4489 868.2006) 
(list 3200.4466 868.2108) 
(list 3200.4433 868.2211) 
(list 3200.4392 868.2314) 
(list 3200.4343 868.2417) 
(list 3200.4288 868.2519) 
(list 3200.4229 868.2622) 
(list 3200.4167 868.2725) 
(list 3200.4104 868.2828) 
(list 3200.4043 868.2931) 
(list 3200.3984 868.3033) 
(list 3200.393 868.3136) 
(list 3200.3883 868.3239) 
(list 3200.3844 868.3342) 
(list 3200.3814 868.3444) 
(list 3200.3795 868.3547) 
(list 3200.3787 868.365) 
(list 3200.3791 868.3753) 
(list 3200.3806 868.3856) 
(list 3200.3832 868.3958) 
(list 3200.3869 868.4061) 
(list 3200.3916 868.4164) 
(list 3200.3971 868.4267) 
(list 3200.4033 868.4369) 
(list 3200.4099 868.4472) 
(list 3200.4169 868.4575) 
(list 3200.4239 868.4678) 
(list 3200.4308 868.4781) 
(list 3200.4374 868.4883) 
(list 3200.4434 868.4986) 
(list 3200.4487 868.5089) 
(list 3200.453 868.5192) 
(list 3200.4563 868.5294) 
(list 3200.4584 868.5397) 
(list 3200.4593 868.55) 
(list 3200.4593 868.55)))
(apply 'command (append '("pline") coords '("c")))
(setq tap10 (ssadd (entlast) tap10))
(command "_mirror" (entlast) "" "3200,900" "3200,901" "No")
(setq tap10 (ssadd (entlast) tap10))
(setq coords (list 
(list 3201.096 868.18) 
(list 3200.4593 868.18) 
(list 3200.4593 868.1903) 
(list 3200.4593 868.2006) 
(list 3200.4593 868.2108) 
(list 3200.4593 868.2211) 
(list 3200.4593 868.2314) 
(list 3200.4593 868.2417) 
(list 3200.4593 868.2519) 
(list 3200.4593 868.2622) 
(list 3200.4593 868.2725) 
(list 3200.4593 868.2828) 
(list 3200.4593 868.2931) 
(list 3200.4593 868.3033) 
(list 3200.4593 868.3136) 
(list 3200.4593 868.3239) 
(list 3200.4593 868.3342) 
(list 3200.4593 868.3444) 
(list 3200.4593 868.3547) 
(list 3200.4593 868.365) 
(list 3200.4593 868.3753) 
(list 3200.4593 868.3856) 
(list 3200.4593 868.3958) 
(list 3200.4593 868.4061) 
(list 3200.4593 868.4164) 
(list 3200.4593 868.4267) 
(list 3200.4593 868.4369) 
(list 3200.4593 868.4472) 
(list 3200.4593 868.4575) 
(list 3200.4593 868.4678) 
(list 3200.4593 868.4781) 
(list 3200.4593 868.4883) 
(list 3200.4593 868.4986) 
(list 3200.4593 868.5089) 
(list 3200.4593 868.5192) 
(list 3200.4593 868.5294) 
(list 3200.4593 868.5397) 
(list 3200.4593 868.55) 
(list 3201.096 868.55)))
(apply 'command (append '("pline") coords '("c")))
(setq tap10 (ssadd (entlast) tap10))
(command "_mirror" (entlast) "" "3200,900" "3200,901" "No")
(setq tap10 (ssadd (entlast) tap10))
(setq coords (list 
(list 3200 868.55) 
(list 3200.135 868.55) 
(list 3200.135 868.5603) 
(list 3200.135 868.5706) 
(list 3200.135 868.5808) 
(list 3200.135 868.5911) 
(list 3200.135 868.6014) 
(list 3200.135 868.6117) 
(list 3200.135 868.6219) 
(list 3200.135 868.6322) 
(list 3200.135 868.6425) 
(list 3200.135 868.6528) 
(list 3200.135 868.6631) 
(list 3200.135 868.6733) 
(list 3200.135 868.6836) 
(list 3200.135 868.6939) 
(list 3200.135 868.7042) 
(list 3200.135 868.7144) 
(list 3200.135 868.7247) 
(list 3200.135 868.735) 
(list 3200.135 868.7453) 
(list 3200.135 868.7556) 
(list 3200.135 868.7658) 
(list 3200.135 868.7761) 
(list 3200.135 868.7864) 
(list 3200.135 868.7967) 
(list 3200.135 868.8069) 
(list 3200.135 868.8172) 
(list 3200.135 868.8275) 
(list 3200.135 868.8378) 
(list 3200.135 868.8481) 
(list 3200.135 868.8583) 
(list 3200.135 868.8686) 
(list 3200.135 868.8789) 
(list 3200.135 868.8892) 
(list 3200.135 868.8994) 
(list 3200.135 868.9097) 
(list 3200.135 868.92) 
(list 3200 868.92)))
(apply 'command (append '("pline") coords '("c")))
(setq tap10 (ssadd (entlast) tap10))
(command "_mirror" (entlast) "" "3200,900" "3200,901" "No")
(setq tap10 (ssadd (entlast) tap10))
(setq coords (list 
(list 3200.4682 868.55) 
(list 3200.4593 868.55) 
(list 3200.4589 868.5603) 
(list 3200.4572 868.5706) 
(list 3200.4543 868.5808) 
(list 3200.4502 868.5911) 
(list 3200.445 868.6014) 
(list 3200.4389 868.6117) 
(list 3200.4321 868.6219) 
(list 3200.4248 868.6322) 
(list 3200.4171 868.6425) 
(list 3200.4094 868.6528) 
(list 3200.4018 868.6631) 
(list 3200.3946 868.6733) 
(list 3200.388 868.6836) 
(list 3200.3822 868.6939) 
(list 3200.3774 868.7042) 
(list 3200.3739 868.7144) 
(list 3200.3716 868.7247) 
(list 3200.3706 868.735) 
(list 3200.3711 868.7453) 
(list 3200.373 868.7556) 
(list 3200.3763 868.7658) 
(list 3200.3809 868.7761) 
(list 3200.3866 868.7864) 
(list 3200.3933 868.7967) 
(list 3200.4008 868.8069) 
(list 3200.4089 868.8172) 
(list 3200.4173 868.8275) 
(list 3200.4258 868.8378) 
(list 3200.4341 868.8481) 
(list 3200.442 868.8583) 
(list 3200.4492 868.8686) 
(list 3200.4556 868.8789) 
(list 3200.4608 868.8892) 
(list 3200.4647 868.8994) 
(list 3200.4672 868.9097) 
(list 3200.4682 868.92) 
(list 3200.4682 868.92)))
(apply 'command (append '("pline") coords '("c")))
(setq tap10 (ssadd (entlast) tap10))
(command "_mirror" (entlast) "" "3200,900" "3200,901" "No")
(setq tap10 (ssadd (entlast) tap10))
(setq coords (list 
(list 3201.096 868.55) 
(list 3200.4682 868.55) 
(list 3200.4682 868.5603) 
(list 3200.4682 868.5706) 
(list 3200.4682 868.5808) 
(list 3200.4682 868.5911) 
(list 3200.4682 868.6014) 
(list 3200.4682 868.6117) 
(list 3200.4682 868.6219) 
(list 3200.4682 868.6322) 
(list 3200.4682 868.6425) 
(list 3200.4682 868.6528) 
(list 3200.4682 868.6631) 
(list 3200.4682 868.6733) 
(list 3200.4682 868.6836) 
(list 3200.4682 868.6939) 
(list 3200.4682 868.7042) 
(list 3200.4682 868.7144) 
(list 3200.4682 868.7247) 
(list 3200.4682 868.735) 
(list 3200.4682 868.7453) 
(list 3200.4682 868.7556) 
(list 3200.4682 868.7658) 
(list 3200.4682 868.7761) 
(list 3200.4682 868.7864) 
(list 3200.4682 868.7967) 
(list 3200.4682 868.8069) 
(list 3200.4682 868.8172) 
(list 3200.4682 868.8275) 
(list 3200.4682 868.8378) 
(list 3200.4682 868.8481) 
(list 3200.4682 868.8583) 
(list 3200.4682 868.8686) 
(list 3200.4682 868.8789) 
(list 3200.4682 868.8892) 
(list 3200.4682 868.8994) 
(list 3200.4682 868.9097) 
(list 3200.4682 868.92) 
(list 3201.096 868.92)))
(apply 'command (append '("pline") coords '("c")))
(setq tap10 (ssadd (entlast) tap10))
(command "_mirror" (entlast) "" "3200,900" "3200,901" "No")
(setq tap10 (ssadd (entlast) tap10))
(setq coords (list 
(list 3200 868.92) 
(list 3200.135 868.92) 
(list 3200.135 868.9303) 
(list 3200.135 868.9406) 
(list 3200.135 868.9508) 
(list 3200.135 868.9611) 
(list 3200.135 868.9714) 
(list 3200.135 868.9817) 
(list 3200.135 868.9919) 
(list 3200.135 869.0022) 
(list 3200.135 869.0125) 
(list 3200.135 869.0228) 
(list 3200.135 869.0331) 
(list 3200.135 869.0433) 
(list 3200.135 869.0536) 
(list 3200.135 869.0639) 
(list 3200.135 869.0742) 
(list 3200.135 869.0844) 
(list 3200.135 869.0947) 
(list 3200.135 869.105) 
(list 3200.135 869.1153) 
(list 3200.135 869.1256) 
(list 3200.135 869.1358) 
(list 3200.135 869.1461) 
(list 3200.135 869.1564) 
(list 3200.135 869.1667) 
(list 3200.135 869.1769) 
(list 3200.135 869.1872) 
(list 3200.135 869.1975) 
(list 3200.135 869.2078) 
(list 3200.135 869.2181) 
(list 3200.135 869.2283) 
(list 3200.135 869.2386) 
(list 3200.135 869.2489) 
(list 3200.135 869.2592) 
(list 3200.135 869.2694) 
(list 3200.135 869.2797) 
(list 3200.135 869.29) 
(list 3200 869.29)))
(apply 'command (append '("pline") coords '("c")))
(setq tap10 (ssadd (entlast) tap10))
(command "_mirror" (entlast) "" "3200,900" "3200,901" "No")
(setq tap10 (ssadd (entlast) tap10))
(setq coords (list 
(list 3200.4771 868.92) 
(list 3200.4682 868.92) 
(list 3200.4677 868.9303) 
(list 3200.4656 868.9406) 
(list 3200.462 868.9508) 
(list 3200.4571 868.9611) 
(list 3200.4509 868.9714) 
(list 3200.4436 868.9817) 
(list 3200.4354 868.9919) 
(list 3200.4266 869.0022) 
(list 3200.4175 869.0125) 
(list 3200.4083 869.0228) 
(list 3200.3993 869.0331) 
(list 3200.3907 869.0433) 
(list 3200.3829 869.0536) 
(list 3200.3761 869.0639) 
(list 3200.3705 869.0742) 
(list 3200.3663 869.0844) 
(list 3200.3636 869.0947) 
(list 3200.3626 869.105) 
(list 3200.3632 869.1153) 
(list 3200.3655 869.1256) 
(list 3200.3694 869.1358) 
(list 3200.3748 869.1461) 
(list 3200.3815 869.1564) 
(list 3200.3894 869.1667) 
(list 3200.3983 869.1769) 
(list 3200.4078 869.1872) 
(list 3200.4177 869.1975) 
(list 3200.4277 869.2078) 
(list 3200.4374 869.2181) 
(list 3200.4467 869.2283) 
(list 3200.4551 869.2386) 
(list 3200.4624 869.2489) 
(list 3200.4685 869.2592) 
(list 3200.473 869.2694) 
(list 3200.4759 869.2797) 
(list 3200.4771 869.29) 
(list 3200.4771 869.29)))
(apply 'command (append '("pline") coords '("c")))
(setq tap10 (ssadd (entlast) tap10))
(command "_mirror" (entlast) "" "3200,900" "3200,901" "No")
(setq tap10 (ssadd (entlast) tap10))
(setq coords (list 
(list 3201.096 868.92) 
(list 3200.4771 868.92) 
(list 3200.4771 868.9303) 
(list 3200.4771 868.9406) 
(list 3200.4771 868.9508) 
(list 3200.4771 868.9611) 
(list 3200.4771 868.9714) 
(list 3200.4771 868.9817) 
(list 3200.4771 868.9919) 
(list 3200.4771 869.0022) 
(list 3200.4771 869.0125) 
(list 3200.4771 869.0228) 
(list 3200.4771 869.0331) 
(list 3200.4771 869.0433) 
(list 3200.4771 869.0536) 
(list 3200.4771 869.0639) 
(list 3200.4771 869.0742) 
(list 3200.4771 869.0844) 
(list 3200.4771 869.0947) 
(list 3200.4771 869.105) 
(list 3200.4771 869.1153) 
(list 3200.4771 869.1256) 
(list 3200.4771 869.1358) 
(list 3200.4771 869.1461) 
(list 3200.4771 869.1564) 
(list 3200.4771 869.1667) 
(list 3200.4771 869.1769) 
(list 3200.4771 869.1872) 
(list 3200.4771 869.1975) 
(list 3200.4771 869.2078) 
(list 3200.4771 869.2181) 
(list 3200.4771 869.2283) 
(list 3200.4771 869.2386) 
(list 3200.4771 869.2489) 
(list 3200.4771 869.2592) 
(list 3200.4771 869.2694) 
(list 3200.4771 869.2797) 
(list 3200.4771 869.29) 
(list 3201.096 869.29)))
(apply 'command (append '("pline") coords '("c")))
(setq tap10 (ssadd (entlast) tap10))
(command "_mirror" (entlast) "" "3200,900" "3200,901" "No")
(setq tap10 (ssadd (entlast) tap10))
(setq coords (list 
(list 3200 869.29) 
(list 3200.135 869.29) 
(list 3200.135 869.3003) 
(list 3200.135 869.3106) 
(list 3200.135 869.3208) 
(list 3200.135 869.3311) 
(list 3200.135 869.3414) 
(list 3200.135 869.3517) 
(list 3200.135 869.3619) 
(list 3200.135 869.3722) 
(list 3200.135 869.3825) 
(list 3200.135 869.3928) 
(list 3200.135 869.4031) 
(list 3200.135 869.4133) 
(list 3200.135 869.4236) 
(list 3200.135 869.4339) 
(list 3200.135 869.4442) 
(list 3200.135 869.4544) 
(list 3200.135 869.4647) 
(list 3200.135 869.475) 
(list 3200.135 869.4853) 
(list 3200.135 869.4956) 
(list 3200.135 869.5058) 
(list 3200.135 869.5161) 
(list 3200.135 869.5264) 
(list 3200.135 869.5367) 
(list 3200.135 869.5469) 
(list 3200.135 869.5572) 
(list 3200.135 869.5675) 
(list 3200.135 869.5778) 
(list 3200.135 869.5881) 
(list 3200.135 869.5983) 
(list 3200.135 869.6086) 
(list 3200.135 869.6189) 
(list 3200.135 869.6292) 
(list 3200.135 869.6394) 
(list 3200.135 869.6497) 
(list 3200.135 869.66) 
(list 3200 869.66)))
(apply 'command (append '("pline") coords '("c")))
(setq tap10 (ssadd (entlast) tap10))
(command "_mirror" (entlast) "" "3200,900" "3200,901" "No")
(setq tap10 (ssadd (entlast) tap10))
(setq coords (list 
(list 3200.4859 869.29) 
(list 3200.4771 869.29) 
(list 3200.4764 869.3003) 
(list 3200.474 869.3106) 
(list 3200.4698 869.3208) 
(list 3200.464 869.3311) 
(list 3200.4567 869.3414) 
(list 3200.4482 869.3517) 
(list 3200.4387 869.3619) 
(list 3200.4285 869.3722) 
(list 3200.4179 869.3825) 
(list 3200.4072 869.3928) 
(list 3200.3968 869.4031) 
(list 3200.3869 869.4133) 
(list 3200.3779 869.4236) 
(list 3200.37 869.4339) 
(list 3200.3636 869.4442) 
(list 3200.3587 869.4544) 
(list 3200.3557 869.4647) 
(list 3200.3545 869.475) 
(list 3200.3552 869.4853) 
(list 3200.3579 869.4956) 
(list 3200.3624 869.5058) 
(list 3200.3687 869.5161) 
(list 3200.3765 869.5264) 
(list 3200.3856 869.5367) 
(list 3200.3958 869.5469) 
(list 3200.4067 869.5572) 
(list 3200.4181 869.5675) 
(list 3200.4295 869.5778) 
(list 3200.4407 869.5881) 
(list 3200.4513 869.5983) 
(list 3200.4609 869.6086) 
(list 3200.4693 869.6189) 
(list 3200.4762 869.6292) 
(list 3200.4814 869.6394) 
(list 3200.4847 869.6497) 
(list 3200.4859 869.66) 
(list 3200.4859 869.66)))
(apply 'command (append '("pline") coords '("c")))
(setq tap10 (ssadd (entlast) tap10))
(command "_mirror" (entlast) "" "3200,900" "3200,901" "No")
(setq tap10 (ssadd (entlast) tap10))
(setq coords (list 
(list 3201.096 869.29) 
(list 3200.4859 869.29) 
(list 3200.4859 869.3003) 
(list 3200.4859 869.3106) 
(list 3200.4859 869.3208) 
(list 3200.4859 869.3311) 
(list 3200.4859 869.3414) 
(list 3200.4859 869.3517) 
(list 3200.4859 869.3619) 
(list 3200.4859 869.3722) 
(list 3200.4859 869.3825) 
(list 3200.4859 869.3928) 
(list 3200.4859 869.4031) 
(list 3200.4859 869.4133) 
(list 3200.4859 869.4236) 
(list 3200.4859 869.4339) 
(list 3200.4859 869.4442) 
(list 3200.4859 869.4544) 
(list 3200.4859 869.4647) 
(list 3200.4859 869.475) 
(list 3200.4859 869.4853) 
(list 3200.4859 869.4956) 
(list 3200.4859 869.5058) 
(list 3200.4859 869.5161) 
(list 3200.4859 869.5264) 
(list 3200.4859 869.5367) 
(list 3200.4859 869.5469) 
(list 3200.4859 869.5572) 
(list 3200.4859 869.5675) 
(list 3200.4859 869.5778) 
(list 3200.4859 869.5881) 
(list 3200.4859 869.5983) 
(list 3200.4859 869.6086) 
(list 3200.4859 869.6189) 
(list 3200.4859 869.6292) 
(list 3200.4859 869.6394) 
(list 3200.4859 869.6497) 
(list 3200.4859 869.66) 
(list 3201.096 869.66)))
(apply 'command (append '("pline") coords '("c")))
(setq tap10 (ssadd (entlast) tap10))
(command "_mirror" (entlast) "" "3200,900" "3200,901" "No")
(setq tap10 (ssadd (entlast) tap10))
(setq coords (list 
(list 3200 869.66) 
(list 3200.135 869.66) 
(list 3200.135 869.6703) 
(list 3200.135 869.6806) 
(list 3200.135 869.6908) 
(list 3200.135 869.7011) 
(list 3200.135 869.7114) 
(list 3200.135 869.7217) 
(list 3200.135 869.7319) 
(list 3200.135 869.7422) 
(list 3200.135 869.7525) 
(list 3200.135 869.7628) 
(list 3200.135 869.7731) 
(list 3200.135 869.7833) 
(list 3200.135 869.7936) 
(list 3200.135 869.8039) 
(list 3200.135 869.8142) 
(list 3200.135 869.8244) 
(list 3200.135 869.8347) 
(list 3200.135 869.845) 
(list 3200.135 869.8553) 
(list 3200.135 869.8656) 
(list 3200.135 869.8758) 
(list 3200.135 869.8861) 
(list 3200.135 869.8964) 
(list 3200.135 869.9067) 
(list 3200.135 869.9169) 
(list 3200.135 869.9272) 
(list 3200.135 869.9375) 
(list 3200.135 869.9478) 
(list 3200.135 869.9581) 
(list 3200.135 869.9683) 
(list 3200.135 869.9786) 
(list 3200.135 869.9889) 
(list 3200.135 869.9992) 
(list 3200.135 870.0094) 
(list 3200.135 870.0197) 
(list 3200.135 870.03) 
(list 3200 870.03)))
(apply 'command (append '("pline") coords '("c")))
(setq tap10 (ssadd (entlast) tap10))
(command "_mirror" (entlast) "" "3200,900" "3200,901" "No")
(setq tap10 (ssadd (entlast) tap10))
(setq coords (list 
(list 3200.4948 869.66) 
(list 3200.4859 869.66) 
(list 3200.4851 869.6703) 
(list 3200.4823 869.6806) 
(list 3200.4775 869.6908) 
(list 3200.4709 869.7011) 
(list 3200.4626 869.7114) 
(list 3200.4528 869.7217) 
(list 3200.442 869.7319) 
(list 3200.4304 869.7422) 
(list 3200.4183 869.7525) 
(list 3200.4061 869.7628) 
(list 3200.3943 869.7731) 
(list 3200.3831 869.7833) 
(list 3200.3728 869.7936) 
(list 3200.3639 869.8039) 
(list 3200.3567 869.8142) 
(list 3200.3512 869.8244) 
(list 3200.3477 869.8347) 
(list 3200.3464 869.845) 
(list 3200.3473 869.8553) 
(list 3200.3504 869.8656) 
(list 3200.3555 869.8758) 
(list 3200.3626 869.8861) 
(list 3200.3714 869.8964) 
(list 3200.3818 869.9067) 
(list 3200.3933 869.9169) 
(list 3200.4057 869.9272) 
(list 3200.4185 869.9375) 
(list 3200.4314 869.9478) 
(list 3200.444 869.9581) 
(list 3200.4559 869.9683) 
(list 3200.4668 869.9786) 
(list 3200.4762 869.9889) 
(list 3200.4839 869.9992) 
(list 3200.4897 870.0094) 
(list 3200.4934 870.0197) 
(list 3200.4948 870.03) 
(list 3200.4948 870.03)))
(apply 'command (append '("pline") coords '("c")))
(setq tap10 (ssadd (entlast) tap10))
(command "_mirror" (entlast) "" "3200,900" "3200,901" "No")
(setq tap10 (ssadd (entlast) tap10))
(setq coords (list 
(list 3201.096 869.66) 
(list 3200.4948 869.66) 
(list 3200.4948 869.6703) 
(list 3200.4948 869.6806) 
(list 3200.4948 869.6908) 
(list 3200.4948 869.7011) 
(list 3200.4948 869.7114) 
(list 3200.4948 869.7217) 
(list 3200.4948 869.7319) 
(list 3200.4948 869.7422) 
(list 3200.4948 869.7525) 
(list 3200.4948 869.7628) 
(list 3200.4948 869.7731) 
(list 3200.4948 869.7833) 
(list 3200.4948 869.7936) 
(list 3200.4948 869.8039) 
(list 3200.4948 869.8142) 
(list 3200.4948 869.8244) 
(list 3200.4948 869.8347) 
(list 3200.4948 869.845) 
(list 3200.4948 869.8553) 
(list 3200.4948 869.8656) 
(list 3200.4948 869.8758) 
(list 3200.4948 869.8861) 
(list 3200.4948 869.8964) 
(list 3200.4948 869.9067) 
(list 3200.4948 869.9169) 
(list 3200.4948 869.9272) 
(list 3200.4948 869.9375) 
(list 3200.4948 869.9478) 
(list 3200.4948 869.9581) 
(list 3200.4948 869.9683) 
(list 3200.4948 869.9786) 
(list 3200.4948 869.9889) 
(list 3200.4948 869.9992) 
(list 3200.4948 870.0094) 
(list 3200.4948 870.0197) 
(list 3200.4948 870.03) 
(list 3201.096 870.03)))
(apply 'command (append '("pline") coords '("c")))
(setq tap10 (ssadd (entlast) tap10))
(command "_mirror" (entlast) "" "3200,900" "3200,901" "No")
(setq tap10 (ssadd (entlast) tap10))
(setq coords (list 
(list 3200 870.03) 
(list 3200.135 870.03) 
(list 3200.135 870.0403) 
(list 3200.135 870.0506) 
(list 3200.135 870.0608) 
(list 3200.135 870.0711) 
(list 3200.135 870.0814) 
(list 3200.135 870.0917) 
(list 3200.135 870.1019) 
(list 3200.135 870.1122) 
(list 3200.135 870.1225) 
(list 3200.135 870.1328) 
(list 3200.135 870.1431) 
(list 3200.135 870.1533) 
(list 3200.135 870.1636) 
(list 3200.135 870.1739) 
(list 3200.135 870.1842) 
(list 3200.135 870.1944) 
(list 3200.135 870.2047) 
(list 3200.135 870.215) 
(list 3200.135 870.2253) 
(list 3200.135 870.2356) 
(list 3200.135 870.2458) 
(list 3200.135 870.2561) 
(list 3200.135 870.2664) 
(list 3200.135 870.2767) 
(list 3200.135 870.2869) 
(list 3200.135 870.2972) 
(list 3200.135 870.3075) 
(list 3200.135 870.3178) 
(list 3200.135 870.3281) 
(list 3200.135 870.3383) 
(list 3200.135 870.3486) 
(list 3200.135 870.3589) 
(list 3200.135 870.3692) 
(list 3200.135 870.3794) 
(list 3200.135 870.3897) 
(list 3200.135 870.4) 
(list 3200 870.4)))
(apply 'command (append '("pline") coords '("c")))
(setq tap10 (ssadd (entlast) tap10))
(command "_mirror" (entlast) "" "3200,900" "3200,901" "No")
(setq tap10 (ssadd (entlast) tap10))
(setq coords (list 
(list 3200.5037 870.03) 
(list 3200.4948 870.03) 
(list 3200.4939 870.0403) 
(list 3200.4907 870.0506) 
(list 3200.4852 870.0608) 
(list 3200.4777 870.0711) 
(list 3200.4684 870.0814) 
(list 3200.4575 870.0917) 
(list 3200.4453 870.1019) 
(list 3200.4322 870.1122) 
(list 3200.4187 870.1225) 
(list 3200.4051 870.1328) 
(list 3200.3918 870.1431) 
(list 3200.3792 870.1533) 
(list 3200.3678 870.1636) 
(list 3200.3579 870.1739) 
(list 3200.3497 870.1842) 
(list 3200.3436 870.1944) 
(list 3200.3398 870.2047) 
(list 3200.3384 870.215) 
(list 3200.3394 870.2253) 
(list 3200.3428 870.2356) 
(list 3200.3486 870.2458) 
(list 3200.3565 870.2561) 
(list 3200.3664 870.2664) 
(list 3200.3779 870.2767) 
(list 3200.3908 870.2869) 
(list 3200.4046 870.2972) 
(list 3200.4189 870.3075) 
(list 3200.4333 870.3178) 
(list 3200.4473 870.3281) 
(list 3200.4606 870.3383) 
(list 3200.4726 870.3486) 
(list 3200.4831 870.3589) 
(list 3200.4917 870.3692) 
(list 3200.4981 870.3794) 
(list 3200.5021 870.3897) 
(list 3200.5037 870.4) 
(list 3200.5037 870.4)))
(apply 'command (append '("pline") coords '("c")))
(setq tap10 (ssadd (entlast) tap10))
(command "_mirror" (entlast) "" "3200,900" "3200,901" "No")
(setq tap10 (ssadd (entlast) tap10))
(setq coords (list 
(list 3201.096 870.03) 
(list 3200.5037 870.03) 
(list 3200.5037 870.0403) 
(list 3200.5037 870.0506) 
(list 3200.5037 870.0608) 
(list 3200.5037 870.0711) 
(list 3200.5037 870.0814) 
(list 3200.5037 870.0917) 
(list 3200.5037 870.1019) 
(list 3200.5037 870.1122) 
(list 3200.5037 870.1225) 
(list 3200.5037 870.1328) 
(list 3200.5037 870.1431) 
(list 3200.5037 870.1533) 
(list 3200.5037 870.1636) 
(list 3200.5037 870.1739) 
(list 3200.5037 870.1842) 
(list 3200.5037 870.1944) 
(list 3200.5037 870.2047) 
(list 3200.5037 870.215) 
(list 3200.5037 870.2253) 
(list 3200.5037 870.2356) 
(list 3200.5037 870.2458) 
(list 3200.5037 870.2561) 
(list 3200.5037 870.2664) 
(list 3200.5037 870.2767) 
(list 3200.5037 870.2869) 
(list 3200.5037 870.2972) 
(list 3200.5037 870.3075) 
(list 3200.5037 870.3178) 
(list 3200.5037 870.3281) 
(list 3200.5037 870.3383) 
(list 3200.5037 870.3486) 
(list 3200.5037 870.3589) 
(list 3200.5037 870.3692) 
(list 3200.5037 870.3794) 
(list 3200.5037 870.3897) 
(list 3200.5037 870.4) 
(list 3201.096 870.4)))
(apply 'command (append '("pline") coords '("c")))
(setq tap10 (ssadd (entlast) tap10))
(command "_mirror" (entlast) "" "3200,900" "3200,901" "No")
(setq tap10 (ssadd (entlast) tap10))
(setq coords (list 
(list 3200 870.4) 
(list 3200.135 870.4) 
(list 3200.135 870.4103) 
(list 3200.135 870.4206) 
(list 3200.135 870.4308) 
(list 3200.135 870.4411) 
(list 3200.135 870.4514) 
(list 3200.135 870.4617) 
(list 3200.135 870.4719) 
(list 3200.135 870.4822) 
(list 3200.135 870.4925) 
(list 3200.135 870.5028) 
(list 3200.135 870.5131) 
(list 3200.135 870.5233) 
(list 3200.135 870.5336) 
(list 3200.135 870.5439) 
(list 3200.135 870.5542) 
(list 3200.135 870.5644) 
(list 3200.135 870.5747) 
(list 3200.135 870.585) 
(list 3200.135 870.5953) 
(list 3200.135 870.6056) 
(list 3200.135 870.6158) 
(list 3200.135 870.6261) 
(list 3200.135 870.6364) 
(list 3200.135 870.6467) 
(list 3200.135 870.6569) 
(list 3200.135 870.6672) 
(list 3200.135 870.6775) 
(list 3200.135 870.6878) 
(list 3200.135 870.6981) 
(list 3200.135 870.7083) 
(list 3200.135 870.7186) 
(list 3200.135 870.7289) 
(list 3200.135 870.7392) 
(list 3200.135 870.7494) 
(list 3200.135 870.7597) 
(list 3200.135 870.77) 
(list 3200 870.77)))
(apply 'command (append '("pline") coords '("c")))
(setq tap10 (ssadd (entlast) tap10))
(command "_mirror" (entlast) "" "3200,900" "3200,901" "No")
(setq tap10 (ssadd (entlast) tap10))
(setq coords (list 
(list 3200.5125 870.4) 
(list 3200.5037 870.4) 
(list 3200.5026 870.4103) 
(list 3200.499 870.4206) 
(list 3200.493 870.4308) 
(list 3200.4846 870.4411) 
(list 3200.4742 870.4514) 
(list 3200.4621 870.4617) 
(list 3200.4486 870.4719) 
(list 3200.4341 870.4822) 
(list 3200.4191 870.4925) 
(list 3200.404 870.5028) 
(list 3200.3893 870.5131) 
(list 3200.3754 870.5233) 
(list 3200.3628 870.5336) 
(list 3200.3518 870.5439) 
(list 3200.3428 870.5542) 
(list 3200.3361 870.5644) 
(list 3200.3319 870.5747) 
(list 3200.3303 870.585) 
(list 3200.3314 870.5953) 
(list 3200.3352 870.6056) 
(list 3200.3416 870.6158) 
(list 3200.3504 870.6261) 
(list 3200.3614 870.6364) 
(list 3200.3741 870.6467) 
(list 3200.3883 870.6569) 
(list 3200.4035 870.6672) 
(list 3200.4193 870.6775) 
(list 3200.4352 870.6878) 
(list 3200.4506 870.6981) 
(list 3200.4652 870.7083) 
(list 3200.4785 870.7186) 
(list 3200.49 870.7289) 
(list 3200.4994 870.7392) 
(list 3200.5065 870.7494) 
(list 3200.5109 870.7597) 
(list 3200.5125 870.77) 
(list 3200.5125 870.77)))
(apply 'command (append '("pline") coords '("c")))
(setq tap10 (ssadd (entlast) tap10))
(command "_mirror" (entlast) "" "3200,900" "3200,901" "No")
(setq tap10 (ssadd (entlast) tap10))
(setq coords (list 
(list 3201.096 870.4) 
(list 3200.5125 870.4) 
(list 3200.5125 870.4103) 
(list 3200.5125 870.4206) 
(list 3200.5125 870.4308) 
(list 3200.5125 870.4411) 
(list 3200.5125 870.4514) 
(list 3200.5125 870.4617) 
(list 3200.5125 870.4719) 
(list 3200.5125 870.4822) 
(list 3200.5125 870.4925) 
(list 3200.5125 870.5028) 
(list 3200.5125 870.5131) 
(list 3200.5125 870.5233) 
(list 3200.5125 870.5336) 
(list 3200.5125 870.5439) 
(list 3200.5125 870.5542) 
(list 3200.5125 870.5644) 
(list 3200.5125 870.5747) 
(list 3200.5125 870.585) 
(list 3200.5125 870.5953) 
(list 3200.5125 870.6056) 
(list 3200.5125 870.6158) 
(list 3200.5125 870.6261) 
(list 3200.5125 870.6364) 
(list 3200.5125 870.6467) 
(list 3200.5125 870.6569) 
(list 3200.5125 870.6672) 
(list 3200.5125 870.6775) 
(list 3200.5125 870.6878) 
(list 3200.5125 870.6981) 
(list 3200.5125 870.7083) 
(list 3200.5125 870.7186) 
(list 3200.5125 870.7289) 
(list 3200.5125 870.7392) 
(list 3200.5125 870.7494) 
(list 3200.5125 870.7597) 
(list 3200.5125 870.77) 
(list 3201.096 870.77)))
(apply 'command (append '("pline") coords '("c")))
(setq tap10 (ssadd (entlast) tap10))
(command "_mirror" (entlast) "" "3200,900" "3200,901" "No")
(setq tap10 (ssadd (entlast) tap10))
(setq coords (list 
(list 3200 870.77) 
(list 3200.135 870.77) 
(list 3200.135 870.7803) 
(list 3200.135 870.7906) 
(list 3200.135 870.8008) 
(list 3200.135 870.8111) 
(list 3200.135 870.8214) 
(list 3200.135 870.8317) 
(list 3200.135 870.8419) 
(list 3200.135 870.8522) 
(list 3200.135 870.8625) 
(list 3200.135 870.8728) 
(list 3200.135 870.8831) 
(list 3200.135 870.8933) 
(list 3200.135 870.9036) 
(list 3200.135 870.9139) 
(list 3200.135 870.9242) 
(list 3200.135 870.9344) 
(list 3200.135 870.9447) 
(list 3200.135 870.955) 
(list 3200.135 870.9653) 
(list 3200.135 870.9756) 
(list 3200.135 870.9858) 
(list 3200.135 870.9961) 
(list 3200.135 871.0064) 
(list 3200.135 871.0167) 
(list 3200.135 871.0269) 
(list 3200.135 871.0372) 
(list 3200.135 871.0475) 
(list 3200.135 871.0578) 
(list 3200.135 871.0681) 
(list 3200.135 871.0783) 
(list 3200.135 871.0886) 
(list 3200.135 871.0989) 
(list 3200.135 871.1092) 
(list 3200.135 871.1194) 
(list 3200.135 871.1297) 
(list 3200.135 871.14) 
(list 3200 871.14)))
(apply 'command (append '("pline") coords '("c")))
(setq tap10 (ssadd (entlast) tap10))
(command "_mirror" (entlast) "" "3200,900" "3200,901" "No")
(setq tap10 (ssadd (entlast) tap10))
(setq coords (list 
(list 3200.5214 870.77) 
(list 3200.5125 870.77) 
(list 3200.5114 870.7803) 
(list 3200.5074 870.7906) 
(list 3200.5007 870.8008) 
(list 3200.4915 870.8111) 
(list 3200.4801 870.8214) 
(list 3200.4667 870.8317) 
(list 3200.4519 870.8419) 
(list 3200.436 870.8522) 
(list 3200.4195 870.8625) 
(list 3200.4029 870.8728) 
(list 3200.3868 870.8831) 
(list 3200.3716 870.8933) 
(list 3200.3577 870.9036) 
(list 3200.3457 870.9139) 
(list 3200.3359 870.9242) 
(list 3200.3285 870.9344) 
(list 3200.3239 870.9447) 
(list 3200.3222 870.955) 
(list 3200.3235 870.9653) 
(list 3200.3277 870.9756) 
(list 3200.3347 870.9858) 
(list 3200.3443 870.9961) 
(list 3200.3563 871.0064) 
(list 3200.3703 871.0167) 
(list 3200.3858 871.0269) 
(list 3200.4025 871.0372) 
(list 3200.4197 871.0475) 
(list 3200.437 871.0578) 
(list 3200.4539 871.0681) 
(list 3200.4698 871.0783) 
(list 3200.4843 871.0886) 
(list 3200.4969 871.0989) 
(list 3200.5071 871.1092) 
(list 3200.5148 871.1194) 
(list 3200.5196 871.1297) 
(list 3200.5214 871.14) 
(list 3200.5214 871.14)))
(apply 'command (append '("pline") coords '("c")))
(setq tap10 (ssadd (entlast) tap10))
(command "_mirror" (entlast) "" "3200,900" "3200,901" "No")
(setq tap10 (ssadd (entlast) tap10))
(setq coords (list 
(list 3201.096 870.77) 
(list 3200.5214 870.77) 
(list 3200.5214 870.7803) 
(list 3200.5214 870.7906) 
(list 3200.5214 870.8008) 
(list 3200.5214 870.8111) 
(list 3200.5214 870.8214) 
(list 3200.5214 870.8317) 
(list 3200.5214 870.8419) 
(list 3200.5214 870.8522) 
(list 3200.5214 870.8625) 
(list 3200.5214 870.8728) 
(list 3200.5214 870.8831) 
(list 3200.5214 870.8933) 
(list 3200.5214 870.9036) 
(list 3200.5214 870.9139) 
(list 3200.5214 870.9242) 
(list 3200.5214 870.9344) 
(list 3200.5214 870.9447) 
(list 3200.5214 870.955) 
(list 3200.5214 870.9653) 
(list 3200.5214 870.9756) 
(list 3200.5214 870.9858) 
(list 3200.5214 870.9961) 
(list 3200.5214 871.0064) 
(list 3200.5214 871.0167) 
(list 3200.5214 871.0269) 
(list 3200.5214 871.0372) 
(list 3200.5214 871.0475) 
(list 3200.5214 871.0578) 
(list 3200.5214 871.0681) 
(list 3200.5214 871.0783) 
(list 3200.5214 871.0886) 
(list 3200.5214 871.0989) 
(list 3200.5214 871.1092) 
(list 3200.5214 871.1194) 
(list 3200.5214 871.1297) 
(list 3200.5214 871.14) 
(list 3201.096 871.14)))
(apply 'command (append '("pline") coords '("c")))
(setq tap10 (ssadd (entlast) tap10))
(command "_mirror" (entlast) "" "3200,900" "3200,901" "No")
(setq tap10 (ssadd (entlast) tap10))
(setq coords (list 
(list 3200 871.14) 
(list 3200.135 871.14) 
(list 3200.135 871.1503) 
(list 3200.135 871.1606) 
(list 3200.135 871.1708) 
(list 3200.135 871.1811) 
(list 3200.135 871.1914) 
(list 3200.135 871.2017) 
(list 3200.135 871.2119) 
(list 3200.135 871.2222) 
(list 3200.135 871.2325) 
(list 3200.135 871.2428) 
(list 3200.135 871.2531) 
(list 3200.135 871.2633) 
(list 3200.135 871.2736) 
(list 3200.135 871.2839) 
(list 3200.135 871.2942) 
(list 3200.135 871.3044) 
(list 3200.135 871.3147) 
(list 3200.135 871.325) 
(list 3200.135 871.3353) 
(list 3200.135 871.3456) 
(list 3200.135 871.3558) 
(list 3200.135 871.3661) 
(list 3200.135 871.3764) 
(list 3200.135 871.3867) 
(list 3200.135 871.3969) 
(list 3200.135 871.4072) 
(list 3200.135 871.4175) 
(list 3200.135 871.4278) 
(list 3200.135 871.4381) 
(list 3200.135 871.4483) 
(list 3200.135 871.4586) 
(list 3200.135 871.4689) 
(list 3200.135 871.4792) 
(list 3200.135 871.4894) 
(list 3200.135 871.4997) 
(list 3200.135 871.51) 
(list 3200 871.51)))
(apply 'command (append '("pline") coords '("c")))
(setq tap10 (ssadd (entlast) tap10))
(command "_mirror" (entlast) "" "3200,900" "3200,901" "No")
(setq tap10 (ssadd (entlast) tap10))
(setq coords (list 
(list 3200.5303 871.14) 
(list 3200.5214 871.14) 
(list 3200.5201 871.1503) 
(list 3200.5157 871.1606) 
(list 3200.5084 871.1708) 
(list 3200.4984 871.1811) 
(list 3200.4859 871.1914) 
(list 3200.4714 871.2017) 
(list 3200.4552 871.2119) 
(list 3200.4379 871.2222) 
(list 3200.4199 871.2325) 
(list 3200.4019 871.2428) 
(list 3200.3843 871.2531) 
(list 3200.3677 871.2633) 
(list 3200.3527 871.2736) 
(list 3200.3396 871.2839) 
(list 3200.3289 871.2942) 
(list 3200.321 871.3044) 
(list 3200.316 871.3147) 
(list 3200.3142 871.325) 
(list 3200.3156 871.3353) 
(list 3200.3201 871.3456) 
(list 3200.3278 871.3558) 
(list 3200.3382 871.3661) 
(list 3200.3513 871.3764) 
(list 3200.3664 871.3867) 
(list 3200.3833 871.3969) 
(list 3200.4014 871.4072) 
(list 3200.4201 871.4175) 
(list 3200.4389 871.4278) 
(list 3200.4572 871.4381) 
(list 3200.4745 871.4483) 
(list 3200.4901 871.4586) 
(list 3200.5038 871.4689) 
(list 3200.5149 871.4792) 
(list 3200.5232 871.4894) 
(list 3200.5284 871.4997) 
(list 3200.5303 871.51) 
(list 3200.5303 871.51)))
(apply 'command (append '("pline") coords '("c")))
(setq tap10 (ssadd (entlast) tap10))
(command "_mirror" (entlast) "" "3200,900" "3200,901" "No")
(setq tap10 (ssadd (entlast) tap10))
(setq coords (list 
(list 3201.096 871.14) 
(list 3200.5303 871.14) 
(list 3200.5303 871.1503) 
(list 3200.5303 871.1606) 
(list 3200.5303 871.1708) 
(list 3200.5303 871.1811) 
(list 3200.5303 871.1914) 
(list 3200.5303 871.2017) 
(list 3200.5303 871.2119) 
(list 3200.5303 871.2222) 
(list 3200.5303 871.2325) 
(list 3200.5303 871.2428) 
(list 3200.5303 871.2531) 
(list 3200.5303 871.2633) 
(list 3200.5303 871.2736) 
(list 3200.5303 871.2839) 
(list 3200.5303 871.2942) 
(list 3200.5303 871.3044) 
(list 3200.5303 871.3147) 
(list 3200.5303 871.325) 
(list 3200.5303 871.3353) 
(list 3200.5303 871.3456) 
(list 3200.5303 871.3558) 
(list 3200.5303 871.3661) 
(list 3200.5303 871.3764) 
(list 3200.5303 871.3867) 
(list 3200.5303 871.3969) 
(list 3200.5303 871.4072) 
(list 3200.5303 871.4175) 
(list 3200.5303 871.4278) 
(list 3200.5303 871.4381) 
(list 3200.5303 871.4483) 
(list 3200.5303 871.4586) 
(list 3200.5303 871.4689) 
(list 3200.5303 871.4792) 
(list 3200.5303 871.4894) 
(list 3200.5303 871.4997) 
(list 3200.5303 871.51) 
(list 3201.096 871.51)))
(apply 'command (append '("pline") coords '("c")))
(setq tap10 (ssadd (entlast) tap10))
(command "_mirror" (entlast) "" "3200,900" "3200,901" "No")
(setq tap10 (ssadd (entlast) tap10))
(setq coords (list 
(list 3200 871.51) 
(list 3200.135 871.51) 
(list 3200.135 871.5203) 
(list 3200.135 871.5306) 
(list 3200.135 871.5408) 
(list 3200.135 871.5511) 
(list 3200.135 871.5614) 
(list 3200.135 871.5717) 
(list 3200.135 871.5819) 
(list 3200.135 871.5922) 
(list 3200.135 871.6025) 
(list 3200.135 871.6128) 
(list 3200.135 871.6231) 
(list 3200.135 871.6333) 
(list 3200.135 871.6436) 
(list 3200.135 871.6539) 
(list 3200.135 871.6642) 
(list 3200.135 871.6744) 
(list 3200.135 871.6847) 
(list 3200.135 871.695) 
(list 3200.135 871.7053) 
(list 3200.135 871.7156) 
(list 3200.135 871.7258) 
(list 3200.135 871.7361) 
(list 3200.135 871.7464) 
(list 3200.135 871.7567) 
(list 3200.135 871.7669) 
(list 3200.135 871.7772) 
(list 3200.135 871.7875) 
(list 3200.135 871.7978) 
(list 3200.135 871.8081) 
(list 3200.135 871.8183) 
(list 3200.135 871.8286) 
(list 3200.135 871.8389) 
(list 3200.135 871.8492) 
(list 3200.135 871.8594) 
(list 3200.135 871.8697) 
(list 3200.135 871.88) 
(list 3200 871.88)))
(apply 'command (append '("pline") coords '("c")))
(setq tap10 (ssadd (entlast) tap10))
(command "_mirror" (entlast) "" "3200,900" "3200,901" "No")
(setq tap10 (ssadd (entlast) tap10))
(setq coords (list 
(list 3200.5391 871.51) 
(list 3200.5303 871.51) 
(list 3200.5288 871.5203) 
(list 3200.5241 871.5306) 
(list 3200.5162 871.5408) 
(list 3200.5053 871.5511) 
(list 3200.4918 871.5614) 
(list 3200.476 871.5717) 
(list 3200.4585 871.5819) 
(list 3200.4397 871.5922) 
(list 3200.4203 871.6025) 
(list 3200.4008 871.6128) 
(list 3200.3818 871.6231) 
(list 3200.3639 871.6333) 
(list 3200.3476 871.6436) 
(list 3200.3335 871.6539) 
(list 3200.322 871.6642) 
(list 3200.3134 871.6744) 
(list 3200.3081 871.6847) 
(list 3200.3061 871.695) 
(list 3200.3076 871.7053) 
(list 3200.3126 871.7156) 
(list 3200.3208 871.7258) 
(list 3200.3322 871.7361) 
(list 3200.3462 871.7464) 
(list 3200.3626 871.7567) 
(list 3200.3808 871.7669) 
(list 3200.4003 871.7772) 
(list 3200.4205 871.7875) 
(list 3200.4408 871.7978) 
(list 3200.4605 871.8081) 
(list 3200.4791 871.8183) 
(list 3200.496 871.8286) 
(list 3200.5106 871.8389) 
(list 3200.5226 871.8492) 
(list 3200.5315 871.8594) 
(list 3200.5371 871.8697) 
(list 3200.5391 871.88) 
(list 3200.5391 871.88)))
(apply 'command (append '("pline") coords '("c")))
(setq tap10 (ssadd (entlast) tap10))
(command "_mirror" (entlast) "" "3200,900" "3200,901" "No")
(setq tap10 (ssadd (entlast) tap10))
(setq coords (list 
(list 3201.096 871.51) 
(list 3200.5391 871.51) 
(list 3200.5391 871.5203) 
(list 3200.5391 871.5306) 
(list 3200.5391 871.5408) 
(list 3200.5391 871.5511) 
(list 3200.5391 871.5614) 
(list 3200.5391 871.5717) 
(list 3200.5391 871.5819) 
(list 3200.5391 871.5922) 
(list 3200.5391 871.6025) 
(list 3200.5391 871.6128) 
(list 3200.5391 871.6231) 
(list 3200.5391 871.6333) 
(list 3200.5391 871.6436) 
(list 3200.5391 871.6539) 
(list 3200.5391 871.6642) 
(list 3200.5391 871.6744) 
(list 3200.5391 871.6847) 
(list 3200.5391 871.695) 
(list 3200.5391 871.7053) 
(list 3200.5391 871.7156) 
(list 3200.5391 871.7258) 
(list 3200.5391 871.7361) 
(list 3200.5391 871.7464) 
(list 3200.5391 871.7567) 
(list 3200.5391 871.7669) 
(list 3200.5391 871.7772) 
(list 3200.5391 871.7875) 
(list 3200.5391 871.7978) 
(list 3200.5391 871.8081) 
(list 3200.5391 871.8183) 
(list 3200.5391 871.8286) 
(list 3200.5391 871.8389) 
(list 3200.5391 871.8492) 
(list 3200.5391 871.8594) 
(list 3200.5391 871.8697) 
(list 3200.5391 871.88) 
(list 3201.096 871.88)))
(apply 'command (append '("pline") coords '("c")))
(setq tap10 (ssadd (entlast) tap10))
(command "_mirror" (entlast) "" "3200,900" "3200,901" "No")
(setq tap10 (ssadd (entlast) tap10))
(setq coords (list 
(list 3200 871.88) 
(list 3200.135 871.88) 
(list 3200.135 871.8903) 
(list 3200.135 871.9006) 
(list 3200.135 871.9108) 
(list 3200.135 871.9211) 
(list 3200.135 871.9314) 
(list 3200.135 871.9417) 
(list 3200.135 871.9519) 
(list 3200.135 871.9622) 
(list 3200.135 871.9725) 
(list 3200.135 871.9828) 
(list 3200.135 871.9931) 
(list 3200.135 872.0033) 
(list 3200.135 872.0136) 
(list 3200.135 872.0239) 
(list 3200.135 872.0342) 
(list 3200.135 872.0444) 
(list 3200.135 872.0547) 
(list 3200.135 872.065) 
(list 3200.135 872.0753) 
(list 3200.135 872.0856) 
(list 3200.135 872.0958) 
(list 3200.135 872.1061) 
(list 3200.135 872.1164) 
(list 3200.135 872.1267) 
(list 3200.135 872.1369) 
(list 3200.135 872.1472) 
(list 3200.135 872.1575) 
(list 3200.135 872.1678) 
(list 3200.135 872.1781) 
(list 3200.135 872.1883) 
(list 3200.135 872.1986) 
(list 3200.135 872.2089) 
(list 3200.135 872.2192) 
(list 3200.135 872.2294) 
(list 3200.135 872.2397) 
(list 3200.135 872.25) 
(list 3200 872.25)))
(apply 'command (append '("pline") coords '("c")))
(setq tap10 (ssadd (entlast) tap10))
(command "_mirror" (entlast) "" "3200,900" "3200,901" "No")
(setq tap10 (ssadd (entlast) tap10))
(setq coords (list 
(list 3200.548 871.88) 
(list 3200.5391 871.88) 
(list 3200.5376 871.8903) 
(list 3200.5325 871.9006) 
(list 3200.5239 871.9108) 
(list 3200.5122 871.9211) 
(list 3200.4976 871.9314) 
(list 3200.4806 871.9417) 
(list 3200.4618 871.9519) 
(list 3200.4416 871.9622) 
(list 3200.4207 871.9725) 
(list 3200.3997 871.9828) 
(list 3200.3793 871.9931) 
(list 3200.3601 872.0033) 
(list 3200.3426 872.0136) 
(list 3200.3274 872.0239) 
(list 3200.3151 872.0342) 
(list 3200.3059 872.0444) 
(list 3200.3001 872.0547) 
(list 3200.298 872.065) 
(list 3200.2997 872.0753) 
(list 3200.305 872.0856) 
(list 3200.3139 872.0958) 
(list 3200.3261 872.1061) 
(list 3200.3412 872.1164) 
(list 3200.3588 872.1267) 
(list 3200.3783 872.1369) 
(list 3200.3992 872.1472) 
(list 3200.4209 872.1575) 
(list 3200.4426 872.1678) 
(list 3200.4638 872.1781) 
(list 3200.4837 872.1883) 
(list 3200.5018 872.1986) 
(list 3200.5175 872.2089) 
(list 3200.5303 872.2192) 
(list 3200.5399 872.2294) 
(list 3200.5458 872.2397) 
(list 3200.548 872.25) 
(list 3200.548 872.25)))
(apply 'command (append '("pline") coords '("c")))
(setq tap10 (ssadd (entlast) tap10))
(command "_mirror" (entlast) "" "3200,900" "3200,901" "No")
(setq tap10 (ssadd (entlast) tap10))
(setq coords (list 
(list 3201.096 871.88) 
(list 3200.548 871.88) 
(list 3200.548 871.8903) 
(list 3200.548 871.9006) 
(list 3200.548 871.9108) 
(list 3200.548 871.9211) 
(list 3200.548 871.9314) 
(list 3200.548 871.9417) 
(list 3200.548 871.9519) 
(list 3200.548 871.9622) 
(list 3200.548 871.9725) 
(list 3200.548 871.9828) 
(list 3200.548 871.9931) 
(list 3200.548 872.0033) 
(list 3200.548 872.0136) 
(list 3200.548 872.0239) 
(list 3200.548 872.0342) 
(list 3200.548 872.0444) 
(list 3200.548 872.0547) 
(list 3200.548 872.065) 
(list 3200.548 872.0753) 
(list 3200.548 872.0856) 
(list 3200.548 872.0958) 
(list 3200.548 872.1061) 
(list 3200.548 872.1164) 
(list 3200.548 872.1267) 
(list 3200.548 872.1369) 
(list 3200.548 872.1472) 
(list 3200.548 872.1575) 
(list 3200.548 872.1678) 
(list 3200.548 872.1781) 
(list 3200.548 872.1883) 
(list 3200.548 872.1986) 
(list 3200.548 872.2089) 
(list 3200.548 872.2192) 
(list 3200.548 872.2294) 
(list 3200.548 872.2397) 
(list 3200.548 872.25) 
(list 3201.096 872.25)))
(apply 'command (append '("pline") coords '("c")))
(setq tap10 (ssadd (entlast) tap10))
(command "_mirror" (entlast) "" "3200,900" "3200,901" "No")
(setq tap10 (ssadd (entlast) tap10))
(command "_block" "blktap10" "3200,900" tap10 "")
(command "_insert" "blktap10" "3200,900" "1" "1" "0")
(command "_insert" "blktap10" "3200,900" "1" "1" "180")
(setq uc10 nil)
(setq uc10 (ssadd))
(setq coords (list 
(list 0 -0.185) 
(list 0.135 -0.185) 
(list 0.135 -0.17472) 
(list 0.135 -0.16444) 
(list 0.135 -0.15417) 
(list 0.135 -0.14389) 
(list 0.135 -0.13361) 
(list 0.135 -0.12333) 
(list 0.135 -0.11306) 
(list 0.135 -0.10278) 
(list 0.135 -0.0925) 
(list 0.135 -0.082222) 
(list 0.135 -0.071944) 
(list 0.135 -0.061667) 
(list 0.135 -0.051389) 
(list 0.135 -0.041111) 
(list 0.135 -0.030833) 
(list 0.135 -0.020556) 
(list 0.135 -0.010278) 
(list 0.135 0) 
(list 0.135 0.010278) 
(list 0.135 0.020556) 
(list 0.135 0.030833) 
(list 0.135 0.041111) 
(list 0.135 0.051389) 
(list 0.135 0.061667) 
(list 0.135 0.071944) 
(list 0.135 0.082222) 
(list 0.135 0.0925) 
(list 0.135 0.10278) 
(list 0.135 0.11306) 
(list 0.135 0.12333) 
(list 0.135 0.13361) 
(list 0.135 0.14389) 
(list 0.135 0.15417) 
(list 0.135 0.16444) 
(list 0.135 0.17472) 
(list 0.135 0.185) 
(list 0 0.185)))
(apply 'command (append '("pline") coords '("c")))
(setq uc10 (ssadd (entlast) uc10))
(setq coords (list 
(list 1.096 -0.185) 
(list 0.548 -0.185) 
(list 0.54607 -0.17472) 
(list 0.54034 -0.16444) 
(list 0.53099 -0.15417) 
(list 0.51829 -0.14389) 
(list 0.50263 -0.13361) 
(list 0.4845 -0.12333) 
(list 0.46444 -0.11306) 
(list 0.44305 -0.10278) 
(list 0.421 -0.0925) 
(list 0.39895 -0.082222) 
(list 0.37756 -0.071944) 
(list 0.3575 -0.061667) 
(list 0.33937 -0.051389) 
(list 0.32371 -0.041111) 
(list 0.31101 -0.030833) 
(list 0.30166 -0.020556) 
(list 0.29593 -0.010278) 
(list 0.294 0) 
(list 0.29593 0.010278) 
(list 0.30166 0.020556) 
(list 0.31101 0.030833) 
(list 0.32371 0.041111) 
(list 0.33937 0.051389) 
(list 0.3575 0.061667) 
(list 0.37756 0.071944) 
(list 0.39895 0.082222) 
(list 0.421 0.0925) 
(list 0.44305 0.10278) 
(list 0.46444 0.11306) 
(list 0.4845 0.12333) 
(list 0.50263 0.13361) 
(list 0.51829 0.14389) 
(list 0.53099 0.15417) 
(list 0.54034 0.16444) 
(list 0.54607 0.17472) 
(list 0.548 0.185) 
(list 1.096 0.185)))
(apply 'command (append '("pline") coords '("c")))
(setq uc10 (ssadd (entlast) uc10))
(command "_block" "blkuc10" "0,0.185" uc10 "")
(command "_insert" "blkuc10" "3200,872.62" "1" "1" "0")
(command "_insert" "blkuc10" "3200,872.25" "1" "1" "180")
(command "_insert" "blkuc10" "3200,872.99" "1" "1" "0")
(command "_insert" "blkuc10" "3200,872.62" "1" "1" "180")
(command "_insert" "blkuc10" "3200,873.36" "1" "1" "0")
(command "_insert" "blkuc10" "3200,872.99" "1" "1" "180")
(command "_insert" "blkuc10" "3200,873.73" "1" "1" "0")
(command "_insert" "blkuc10" "3200,873.36" "1" "1" "180")
(command "_insert" "blkuc10" "3200,874.1" "1" "1" "0")
(command "_insert" "blkuc10" "3200,873.73" "1" "1" "180")
(command "_insert" "blkuc10" "3200,874.47" "1" "1" "0")
(command "_insert" "blkuc10" "3200,874.1" "1" "1" "180")
(command "_insert" "blkuc10" "3200,874.84" "1" "1" "0")
(command "_insert" "blkuc10" "3200,874.47" "1" "1" "180")
(command "_insert" "blkuc10" "3200,875.21" "1" "1" "0")
(command "_insert" "blkuc10" "3200,874.84" "1" "1" "180")
(command "_insert" "blkuc10" "3200,875.58" "1" "1" "0")
(command "_insert" "blkuc10" "3200,875.21" "1" "1" "180")
(command "_insert" "blkuc10" "3200,875.95" "1" "1" "0")
(command "_insert" "blkuc10" "3200,875.58" "1" "1" "180")
(command "_insert" "blkuc10" "3200,876.32" "1" "1" "0")
(command "_insert" "blkuc10" "3200,875.95" "1" "1" "180")
(command "_insert" "blkuc10" "3200,876.69" "1" "1" "0")
(command "_insert" "blkuc10" "3200,876.32" "1" "1" "180")
(command "_insert" "blkuc10" "3200,877.06" "1" "1" "0")
(command "_insert" "blkuc10" "3200,876.69" "1" "1" "180")
(command "_insert" "blkuc10" "3200,877.43" "1" "1" "0")
(command "_insert" "blkuc10" "3200,877.06" "1" "1" "180")
(command "_insert" "blkuc10" "3200,877.8" "1" "1" "0")
(command "_insert" "blkuc10" "3200,877.43" "1" "1" "180")
(command "_insert" "blkuc10" "3200,878.17" "1" "1" "0")
(command "_insert" "blkuc10" "3200,877.8" "1" "1" "180")
(command "_insert" "blkuc10" "3200,878.54" "1" "1" "0")
(command "_insert" "blkuc10" "3200,878.17" "1" "1" "180")
(command "_insert" "blkuc10" "3200,878.91" "1" "1" "0")
(command "_insert" "blkuc10" "3200,878.54" "1" "1" "180")
(command "_insert" "blkuc10" "3200,879.28" "1" "1" "0")
(command "_insert" "blkuc10" "3200,878.91" "1" "1" "180")
(command "_insert" "blkuc10" "3200,879.65" "1" "1" "0")
(command "_insert" "blkuc10" "3200,879.28" "1" "1" "180")
(command "_insert" "blkuc10" "3200,880.02" "1" "1" "0")
(command "_insert" "blkuc10" "3200,879.65" "1" "1" "180")
(command "_insert" "blkuc10" "3200,880.39" "1" "1" "0")
(command "_insert" "blkuc10" "3200,880.02" "1" "1" "180")
(command "_insert" "blkuc10" "3200,880.76" "1" "1" "0")
(command "_insert" "blkuc10" "3200,880.39" "1" "1" "180")
(command "_insert" "blkuc10" "3200,881.13" "1" "1" "0")
(command "_insert" "blkuc10" "3200,880.76" "1" "1" "180")
(command "_insert" "blkuc10" "3200,881.5" "1" "1" "0")
(command "_insert" "blkuc10" "3200,881.13" "1" "1" "180")
(command "_insert" "blkuc10" "3200,881.87" "1" "1" "0")
(command "_insert" "blkuc10" "3200,881.5" "1" "1" "180")
(command "_insert" "blkuc10" "3200,882.24" "1" "1" "0")
(command "_insert" "blkuc10" "3200,881.87" "1" "1" "180")
(command "_insert" "blkuc10" "3200,882.61" "1" "1" "0")
(command "_insert" "blkuc10" "3200,882.24" "1" "1" "180")
(command "_insert" "blkuc10" "3200,882.98" "1" "1" "0")
(command "_insert" "blkuc10" "3200,882.61" "1" "1" "180")
(command "_insert" "blkuc10" "3200,883.35" "1" "1" "0")
(command "_insert" "blkuc10" "3200,882.98" "1" "1" "180")
(command "_insert" "blkuc10" "3200,883.72" "1" "1" "0")
(command "_insert" "blkuc10" "3200,883.35" "1" "1" "180")
(command "_insert" "blkuc10" "3200,884.09" "1" "1" "0")
(command "_insert" "blkuc10" "3200,883.72" "1" "1" "180")
(command "_insert" "blkuc10" "3200,884.46" "1" "1" "0")
(command "_insert" "blkuc10" "3200,884.09" "1" "1" "180")
(command "_insert" "blkuc10" "3200,884.83" "1" "1" "0")
(command "_insert" "blkuc10" "3200,884.46" "1" "1" "180")
(command "_insert" "blkuc10" "3200,885.2" "1" "1" "0")
(command "_insert" "blkuc10" "3200,884.83" "1" "1" "180")
(command "_insert" "blkuc10" "3200,885.57" "1" "1" "0")
(command "_insert" "blkuc10" "3200,885.2" "1" "1" "180")
(command "_insert" "blkuc10" "3200,885.94" "1" "1" "0")
(command "_insert" "blkuc10" "3200,885.57" "1" "1" "180")
(command "_insert" "blkuc10" "3200,886.31" "1" "1" "0")
(command "_insert" "blkuc10" "3200,885.94" "1" "1" "180")
(command "_insert" "blkuc10" "3200,886.68" "1" "1" "0")
(command "_insert" "blkuc10" "3200,886.31" "1" "1" "180")
(command "_insert" "blkuc10" "3200,887.05" "1" "1" "0")
(command "_insert" "blkuc10" "3200,886.68" "1" "1" "180")
(command "_insert" "blkuc10" "3200,887.42" "1" "1" "0")
(command "_insert" "blkuc10" "3200,887.05" "1" "1" "180")
(command "_insert" "blkuc10" "3200,887.79" "1" "1" "0")
(command "_insert" "blkuc10" "3200,887.42" "1" "1" "180")
(command "_insert" "blkuc10" "3200,888.16" "1" "1" "0")
(command "_insert" "blkuc10" "3200,887.79" "1" "1" "180")
(command "_insert" "blkuc10" "3200,888.53" "1" "1" "0")
(command "_insert" "blkuc10" "3200,888.16" "1" "1" "180")
(command "_insert" "blkuc10" "3200,888.9" "1" "1" "0")
(command "_insert" "blkuc10" "3200,888.53" "1" "1" "180")
(command "_insert" "blkuc10" "3200,889.27" "1" "1" "0")
(command "_insert" "blkuc10" "3200,888.9" "1" "1" "180")
(command "_insert" "blkuc10" "3200,889.64" "1" "1" "0")
(command "_insert" "blkuc10" "3200,889.27" "1" "1" "180")
(command "_insert" "blkuc10" "3200,890.01" "1" "1" "0")
(command "_insert" "blkuc10" "3200,889.64" "1" "1" "180")
(command "_insert" "blkuc10" "3200,890.38" "1" "1" "0")
(command "_insert" "blkuc10" "3200,890.01" "1" "1" "180")
(command "_insert" "blkuc10" "3200,890.75" "1" "1" "0")
(command "_insert" "blkuc10" "3200,890.38" "1" "1" "180")
(command "_insert" "blkuc10" "3200,891.12" "1" "1" "0")
(command "_insert" "blkuc10" "3200,890.75" "1" "1" "180")
(command "_insert" "blkuc10" "3200,891.49" "1" "1" "0")
(command "_insert" "blkuc10" "3200,891.12" "1" "1" "180")
(command "_insert" "blkuc10" "3200,891.86" "1" "1" "0")
(command "_insert" "blkuc10" "3200,891.49" "1" "1" "180")
(command "_insert" "blkuc10" "3200,892.23" "1" "1" "0")
(command "_insert" "blkuc10" "3200,891.86" "1" "1" "180")
(command "_insert" "blkuc10" "3200,892.6" "1" "1" "0")
(command "_insert" "blkuc10" "3200,892.23" "1" "1" "180")
(command "_insert" "blkuc10" "3200,892.97" "1" "1" "0")
(command "_insert" "blkuc10" "3200,892.6" "1" "1" "180")
(command "_insert" "blkuc10" "3200,893.34" "1" "1" "0")
(command "_insert" "blkuc10" "3200,892.97" "1" "1" "180")
(command "_insert" "blkuc10" "3200,893.71" "1" "1" "0")
(command "_insert" "blkuc10" "3200,893.34" "1" "1" "180")
(command "_insert" "blkuc10" "3200,894.08" "1" "1" "0")
(command "_insert" "blkuc10" "3200,893.71" "1" "1" "180")
(command "_insert" "blkuc10" "3200,894.45" "1" "1" "0")
(command "_insert" "blkuc10" "3200,894.08" "1" "1" "180")
(command "_insert" "blkuc10" "3200,894.82" "1" "1" "0")
(command "_insert" "blkuc10" "3200,894.45" "1" "1" "180")
(command "_insert" "blkuc10" "3200,895.19" "1" "1" "0")
(command "_insert" "blkuc10" "3200,894.82" "1" "1" "180")
(command "_insert" "blkuc10" "3200,895.56" "1" "1" "0")
(command "_insert" "blkuc10" "3200,895.19" "1" "1" "180")
(command "_insert" "blkuc10" "3200,895.93" "1" "1" "0")
(command "_insert" "blkuc10" "3200,895.56" "1" "1" "180")
(command "_insert" "blkuc10" "3200,896.3" "1" "1" "0")
(command "_insert" "blkuc10" "3200,895.93" "1" "1" "180")
(command "_insert" "blkuc10" "3200,896.67" "1" "1" "0")
(command "_insert" "blkuc10" "3200,896.3" "1" "1" "180")
(command "_insert" "blkuc10" "3200,897.04" "1" "1" "0")
(command "_insert" "blkuc10" "3200,896.67" "1" "1" "180")
(command "_insert" "blkuc10" "3200,897.41" "1" "1" "0")
(command "_insert" "blkuc10" "3200,897.04" "1" "1" "180")
(command "_insert" "blkuc10" "3200,897.78" "1" "1" "0")
(command "_insert" "blkuc10" "3200,897.41" "1" "1" "180")
(command "_insert" "blkuc10" "3200,898.15" "1" "1" "0")
(command "_insert" "blkuc10" "3200,897.78" "1" "1" "180")
(command "_insert" "blkuc10" "3200,898.52" "1" "1" "0")
(command "_insert" "blkuc10" "3200,898.15" "1" "1" "180")
(command "_insert" "blkuc10" "3200,898.89" "1" "1" "0")
(command "_insert" "blkuc10" "3200,898.52" "1" "1" "180")
(command "_insert" "blkuc10" "3200,899.26" "1" "1" "0")
(command "_insert" "blkuc10" "3200,898.89" "1" "1" "180")
(command "_insert" "blkuc10" "3200,899.63" "1" "1" "0")
(command "_insert" "blkuc10" "3200,899.26" "1" "1" "180")
(command "_insert" "blkuc10" "3200,900" "1" "1" "0")
(command "_insert" "blkuc10" "3200,899.63" "1" "1" "180")
(command "_insert" "blkuc10" "3200,900.37" "1" "1" "0")
(command "_insert" "blkuc10" "3200,900" "1" "1" "180")
(command "_insert" "blkuc10" "3200,900.74" "1" "1" "0")
(command "_insert" "blkuc10" "3200,900.37" "1" "1" "180")
(command "_insert" "blkuc10" "3200,901.11" "1" "1" "0")
(command "_insert" "blkuc10" "3200,900.74" "1" "1" "180")
(command "_insert" "blkuc10" "3200,901.48" "1" "1" "0")
(command "_insert" "blkuc10" "3200,901.11" "1" "1" "180")
(command "_insert" "blkuc10" "3200,901.85" "1" "1" "0")
(command "_insert" "blkuc10" "3200,901.48" "1" "1" "180")
(command "_insert" "blkuc10" "3200,902.22" "1" "1" "0")
(command "_insert" "blkuc10" "3200,901.85" "1" "1" "180")
(command "_insert" "blkuc10" "3200,902.59" "1" "1" "0")
(command "_insert" "blkuc10" "3200,902.22" "1" "1" "180")
(command "_insert" "blkuc10" "3200,902.96" "1" "1" "0")
(command "_insert" "blkuc10" "3200,902.59" "1" "1" "180")
(command "_insert" "blkuc10" "3200,903.33" "1" "1" "0")
(command "_insert" "blkuc10" "3200,902.96" "1" "1" "180")
(command "_insert" "blkuc10" "3200,903.7" "1" "1" "0")
(command "_insert" "blkuc10" "3200,903.33" "1" "1" "180")
(command "_insert" "blkuc10" "3200,904.07" "1" "1" "0")
(command "_insert" "blkuc10" "3200,903.7" "1" "1" "180")
(command "_insert" "blkuc10" "3200,904.44" "1" "1" "0")
(command "_insert" "blkuc10" "3200,904.07" "1" "1" "180")
(command "_insert" "blkuc10" "3200,904.81" "1" "1" "0")
(command "_insert" "blkuc10" "3200,904.44" "1" "1" "180")
(command "_insert" "blkuc10" "3200,905.18" "1" "1" "0")
(command "_insert" "blkuc10" "3200,904.81" "1" "1" "180")
(command "_insert" "blkuc10" "3200,905.55" "1" "1" "0")
(command "_insert" "blkuc10" "3200,905.18" "1" "1" "180")
(command "_insert" "blkuc10" "3200,905.92" "1" "1" "0")
(command "_insert" "blkuc10" "3200,905.55" "1" "1" "180")
(command "_insert" "blkuc10" "3200,906.29" "1" "1" "0")
(command "_insert" "blkuc10" "3200,905.92" "1" "1" "180")
(command "_insert" "blkuc10" "3200,906.66" "1" "1" "0")
(command "_insert" "blkuc10" "3200,906.29" "1" "1" "180")
(command "_insert" "blkuc10" "3200,907.03" "1" "1" "0")
(command "_insert" "blkuc10" "3200,906.66" "1" "1" "180")
(command "_insert" "blkuc10" "3200,907.4" "1" "1" "0")
(command "_insert" "blkuc10" "3200,907.03" "1" "1" "180")
(command "_insert" "blkuc10" "3200,907.77" "1" "1" "0")
(command "_insert" "blkuc10" "3200,907.4" "1" "1" "180")
(command "_insert" "blkuc10" "3200,908.14" "1" "1" "0")
(command "_insert" "blkuc10" "3200,907.77" "1" "1" "180")
(command "_insert" "blkuc10" "3200,908.51" "1" "1" "0")
(command "_insert" "blkuc10" "3200,908.14" "1" "1" "180")
(command "_insert" "blkuc10" "3200,908.88" "1" "1" "0")
(command "_insert" "blkuc10" "3200,908.51" "1" "1" "180")
(command "_insert" "blkuc10" "3200,909.25" "1" "1" "0")
(command "_insert" "blkuc10" "3200,908.88" "1" "1" "180")
(command "_insert" "blkuc10" "3200,909.62" "1" "1" "0")
(command "_insert" "blkuc10" "3200,909.25" "1" "1" "180")
(command "_insert" "blkuc10" "3200,909.99" "1" "1" "0")
(command "_insert" "blkuc10" "3200,909.62" "1" "1" "180")
(command "_insert" "blkuc10" "3200,910.36" "1" "1" "0")
(command "_insert" "blkuc10" "3200,909.99" "1" "1" "180")
(command "_insert" "blkuc10" "3200,910.73" "1" "1" "0")
(command "_insert" "blkuc10" "3200,910.36" "1" "1" "180")
(command "_insert" "blkuc10" "3200,911.1" "1" "1" "0")
(command "_insert" "blkuc10" "3200,910.73" "1" "1" "180")
(command "_insert" "blkuc10" "3200,911.47" "1" "1" "0")
(command "_insert" "blkuc10" "3200,911.1" "1" "1" "180")
(command "_insert" "blkuc10" "3200,911.84" "1" "1" "0")
(command "_insert" "blkuc10" "3200,911.47" "1" "1" "180")
(command "_insert" "blkuc10" "3200,912.21" "1" "1" "0")
(command "_insert" "blkuc10" "3200,911.84" "1" "1" "180")
(command "_insert" "blkuc10" "3200,912.58" "1" "1" "0")
(command "_insert" "blkuc10" "3200,912.21" "1" "1" "180")
(command "_insert" "blkuc10" "3200,912.95" "1" "1" "0")
(command "_insert" "blkuc10" "3200,912.58" "1" "1" "180")
(command "_insert" "blkuc10" "3200,913.32" "1" "1" "0")
(command "_insert" "blkuc10" "3200,912.95" "1" "1" "180")
(command "_insert" "blkuc10" "3200,913.69" "1" "1" "0")
(command "_insert" "blkuc10" "3200,913.32" "1" "1" "180")
(command "_insert" "blkuc10" "3200,914.06" "1" "1" "0")
(command "_insert" "blkuc10" "3200,913.69" "1" "1" "180")
(command "_insert" "blkuc10" "3200,914.43" "1" "1" "0")
(command "_insert" "blkuc10" "3200,914.06" "1" "1" "180")
(command "_insert" "blkuc10" "3200,914.8" "1" "1" "0")
(command "_insert" "blkuc10" "3200,914.43" "1" "1" "180")
(command "_insert" "blkuc10" "3200,915.17" "1" "1" "0")
(command "_insert" "blkuc10" "3200,914.8" "1" "1" "180")
(command "_insert" "blkuc10" "3200,915.54" "1" "1" "0")
(command "_insert" "blkuc10" "3200,915.17" "1" "1" "180")
(command "_insert" "blkuc10" "3200,915.91" "1" "1" "0")
(command "_insert" "blkuc10" "3200,915.54" "1" "1" "180")
(command "_insert" "blkuc10" "3200,916.28" "1" "1" "0")
(command "_insert" "blkuc10" "3200,915.91" "1" "1" "180")
(command "_insert" "blkuc10" "3200,916.65" "1" "1" "0")
(command "_insert" "blkuc10" "3200,916.28" "1" "1" "180")
(command "_insert" "blkuc10" "3200,917.02" "1" "1" "0")
(command "_insert" "blkuc10" "3200,916.65" "1" "1" "180")
(command "_insert" "blkuc10" "3200,917.39" "1" "1" "0")
(command "_insert" "blkuc10" "3200,917.02" "1" "1" "180")
(command "_insert" "blkuc10" "3200,917.76" "1" "1" "0")
(command "_insert" "blkuc10" "3200,917.39" "1" "1" "180")
(command "_insert" "blkuc10" "3200,918.13" "1" "1" "0")
(command "_insert" "blkuc10" "3200,917.76" "1" "1" "180")
(command "_insert" "blkuc10" "3200,918.5" "1" "1" "0")
(command "_insert" "blkuc10" "3200,918.13" "1" "1" "180")
(command "_insert" "blkuc10" "3200,918.87" "1" "1" "0")
(command "_insert" "blkuc10" "3200,918.5" "1" "1" "180")
(command "_insert" "blkuc10" "3200,919.24" "1" "1" "0")
(command "_insert" "blkuc10" "3200,918.87" "1" "1" "180")
(command "_insert" "blkuc10" "3200,919.61" "1" "1" "0")
(command "_insert" "blkuc10" "3200,919.24" "1" "1" "180")
(command "_insert" "blkuc10" "3200,919.98" "1" "1" "0")
(command "_insert" "blkuc10" "3200,919.61" "1" "1" "180")
(command "_insert" "blkuc10" "3200,920.35" "1" "1" "0")
(command "_insert" "blkuc10" "3200,919.98" "1" "1" "180")
(command "_insert" "blkuc10" "3200,920.72" "1" "1" "0")
(command "_insert" "blkuc10" "3200,920.35" "1" "1" "180")
(command "_insert" "blkuc10" "3200,921.09" "1" "1" "0")
(command "_insert" "blkuc10" "3200,920.72" "1" "1" "180")
(command "_insert" "blkuc10" "3200,921.46" "1" "1" "0")
(command "_insert" "blkuc10" "3200,921.09" "1" "1" "180")
(command "_insert" "blkuc10" "3200,921.83" "1" "1" "0")
(command "_insert" "blkuc10" "3200,921.46" "1" "1" "180")
(command "_insert" "blkuc10" "3200,922.2" "1" "1" "0")
(command "_insert" "blkuc10" "3200,921.83" "1" "1" "180")
(command "_insert" "blkuc10" "3200,922.57" "1" "1" "0")
(command "_insert" "blkuc10" "3200,922.2" "1" "1" "180")
(command "_insert" "blkuc10" "3200,922.94" "1" "1" "0")
(command "_insert" "blkuc10" "3200,922.57" "1" "1" "180")
(command "_insert" "blkuc10" "3200,923.31" "1" "1" "0")
(command "_insert" "blkuc10" "3200,922.94" "1" "1" "180")
(command "_insert" "blkuc10" "3200,923.68" "1" "1" "0")
(command "_insert" "blkuc10" "3200,923.31" "1" "1" "180")
(command "_insert" "blkuc10" "3200,924.05" "1" "1" "0")
(command "_insert" "blkuc10" "3200,923.68" "1" "1" "180")
(command "_insert" "blkuc10" "3200,924.42" "1" "1" "0")
(command "_insert" "blkuc10" "3200,924.05" "1" "1" "180")
(command "_insert" "blkuc10" "3200,924.79" "1" "1" "0")
(command "_insert" "blkuc10" "3200,924.42" "1" "1" "180")
(command "_insert" "blkuc10" "3200,925.16" "1" "1" "0")
(command "_insert" "blkuc10" "3200,924.79" "1" "1" "180")
(command "_insert" "blkuc10" "3200,925.53" "1" "1" "0")
(command "_insert" "blkuc10" "3200,925.16" "1" "1" "180")
(command "_insert" "blkuc10" "3200,925.9" "1" "1" "0")
(command "_insert" "blkuc10" "3200,925.53" "1" "1" "180")
(command "_insert" "blkuc10" "3200,926.27" "1" "1" "0")
(command "_insert" "blkuc10" "3200,925.9" "1" "1" "180")
(command "_insert" "blkuc10" "3200,926.64" "1" "1" "0")
(command "_insert" "blkuc10" "3200,926.27" "1" "1" "180")
(command "_insert" "blkuc10" "3200,927.01" "1" "1" "0")
(command "_insert" "blkuc10" "3200,926.64" "1" "1" "180")
(command "_insert" "blkuc10" "3200,927.38" "1" "1" "0")
(command "_insert" "blkuc10" "3200,927.01" "1" "1" "180")
(command "_insert" "blkuc10" "3200,927.75" "1" "1" "0")
(command "_insert" "blkuc10" "3200,927.38" "1" "1" "180")
(command "_layer" "set" "phccover" "")
(command "_rectangle" "3198.904,933.3" "3201.096,866.7")
(command "_layer" "set" "nitride" "")
(setq phc10 currobj)
(command "_layer" "set" "cover" "")
(command "_rectangle" "3198.904,836.7" "3201.096,963.3")
(command "_layer" "set" "nitride" "")
(command "_layer" "set" "text" "")
(command "_circle" "3197.954,846.7" "0.075")
(command "_circle" "3197.579,846.7" "0.15")
(command "_circle" "3197.204,846.7" "0.075")
(command "_circle" "3196.829,846.7" "0.15")
(command "_circle" "3197.954,848.7" "0.075")
(command "_circle" "3197.579,848.7" "0.075")
(command "_circle" "3197.204,848.7" "0.15")
(command "_circle" "3196.829,848.7" "0.15")
(command "_circle" "3197.954,850.7" "0.075")
(command "_circle" "3197.579,850.7" "0.15")
(command "_circle" "3197.204,850.7" "0.15")
(command "_circle" "3196.829,850.7" "0.15")
(command "_circle" "3197.954,852.7" "0.075")
(command "_circle" "3197.579,852.7" "0.075")
(command "_circle" "3197.204,852.7" "0.075")
(command "_circle" "3196.829,852.7" "0.075")
(command "_circle" "3196.454,852.7" "0.15")
(command "_circle" "3197.954,854.7" "0.075")
(command "_circle" "3197.579,854.7" "0.15")
(command "_circle" "3197.204,854.7" "0.075")
(command "_circle" "3196.829,854.7" "0.075")
(command "_circle" "3196.454,854.7" "0.15")
(command "_circle" "3197.954,856.7" "0.075")
(command "_circle" "3197.579,856.7" "0.075")
(command "_circle" "3197.204,856.7" "0.15")
(command "_circle" "3196.829,856.7" "0.075")
(command "_circle" "3196.454,856.7" "0.15")
(command "_circle" "3197.954,858.7" "0.075")
(command "_circle" "3197.579,858.7" "0.15")
(command "_circle" "3197.204,858.7" "0.15")
(command "_circle" "3196.829,858.7" "0.075")
(command "_circle" "3196.454,858.7" "0.15")
(command "_circle" "3197.954,860.7" "0.075")
(command "_circle" "3197.579,860.7" "0.075")
(command "_circle" "3197.204,860.7" "0.075")
(command "_circle" "3196.829,860.7" "0.15")
(command "_circle" "3196.454,860.7" "0.15")
(command "_circle" "3197.954,862.7" "0.075")
(command "_circle" "3197.579,862.7" "0.15")
(command "_circle" "3197.204,862.7" "0.075")
(command "_circle" "3196.829,862.7" "0.15")
(command "_circle" "3196.454,862.7" "0.15")
(command "_circle" "3197.954,864.7" "0.075")
(command "_circle" "3197.579,864.7" "0.075")
(command "_circle" "3197.204,864.7" "0.15")
(command "_circle" "3196.829,864.7" "0.15")
(command "_circle" "3196.454,864.7" "0.15")
(command "_circle" "3197.954,866.7" "0.075")
(command "_circle" "3197.579,866.7" "0.15")
(command "_circle" "3197.204,866.7" "0.15")
(command "_circle" "3196.829,866.7" "0.15")
(command "_circle" "3196.454,866.7" "0.15")
(command "_circle" "3197.954,868.7" "0.075")
(command "_circle" "3197.579,868.7" "0.075")
(command "_circle" "3197.204,868.7" "0.075")
(command "_circle" "3196.829,868.7" "0.075")
(command "_circle" "3196.454,868.7" "0.075")
(command "_circle" "3196.079,868.7" "0.15")
(command "_circle" "3197.954,870.7" "0.075")
(command "_circle" "3197.579,870.7" "0.15")
(command "_circle" "3197.204,870.7" "0.075")
(command "_circle" "3196.829,870.7" "0.075")
(command "_circle" "3196.454,870.7" "0.075")
(command "_circle" "3196.079,870.7" "0.15")
(command "_circle" "3197.954,872.7" "0.075")
(command "_circle" "3197.579,872.7" "0.075")
(command "_circle" "3197.204,872.7" "0.15")
(command "_circle" "3196.829,872.7" "0.075")
(command "_circle" "3196.454,872.7" "0.075")
(command "_circle" "3196.079,872.7" "0.15")
(command "_circle" "3197.954,874.7" "0.075")
(command "_circle" "3197.579,874.7" "0.15")
(command "_circle" "3197.204,874.7" "0.15")
(command "_circle" "3196.829,874.7" "0.075")
(command "_circle" "3196.454,874.7" "0.075")
(command "_circle" "3196.079,874.7" "0.15")
(command "_circle" "3197.954,876.7" "0.075")
(command "_circle" "3197.579,876.7" "0.075")
(command "_circle" "3197.204,876.7" "0.075")
(command "_circle" "3196.829,876.7" "0.15")
(command "_circle" "3196.454,876.7" "0.075")
(command "_circle" "3196.079,876.7" "0.15")
(command "_circle" "3197.954,878.7" "0.075")
(command "_circle" "3197.579,878.7" "0.15")
(command "_circle" "3197.204,878.7" "0.075")
(command "_circle" "3196.829,878.7" "0.15")
(command "_circle" "3196.454,878.7" "0.075")
(command "_circle" "3196.079,878.7" "0.15")
(command "_circle" "3197.954,880.7" "0.075")
(command "_circle" "3197.579,880.7" "0.075")
(command "_circle" "3197.204,880.7" "0.15")
(command "_circle" "3196.829,880.7" "0.15")
(command "_circle" "3196.454,880.7" "0.075")
(command "_circle" "3196.079,880.7" "0.15")
(command "_circle" "3197.954,882.7" "0.075")
(command "_circle" "3197.579,882.7" "0.15")
(command "_circle" "3197.204,882.7" "0.15")
(command "_circle" "3196.829,882.7" "0.15")
(command "_circle" "3196.454,882.7" "0.075")
(command "_circle" "3196.079,882.7" "0.15")
(command "_circle" "3197.954,884.7" "0.075")
(command "_circle" "3197.579,884.7" "0.075")
(command "_circle" "3197.204,884.7" "0.075")
(command "_circle" "3196.829,884.7" "0.075")
(command "_circle" "3196.454,884.7" "0.15")
(command "_circle" "3196.079,884.7" "0.15")
(command "_circle" "3197.954,886.7" "0.075")
(command "_circle" "3197.579,886.7" "0.15")
(command "_circle" "3197.204,886.7" "0.075")
(command "_circle" "3196.829,886.7" "0.075")
(command "_circle" "3196.454,886.7" "0.15")
(command "_circle" "3196.079,886.7" "0.15")
(command "_circle" "3197.954,888.7" "0.075")
(command "_circle" "3197.579,888.7" "0.075")
(command "_circle" "3197.204,888.7" "0.15")
(command "_circle" "3196.829,888.7" "0.075")
(command "_circle" "3196.454,888.7" "0.15")
(command "_circle" "3196.079,888.7" "0.15")
(command "_circle" "3197.954,890.7" "0.075")
(command "_circle" "3197.579,890.7" "0.15")
(command "_circle" "3197.204,890.7" "0.15")
(command "_circle" "3196.829,890.7" "0.075")
(command "_circle" "3196.454,890.7" "0.15")
(command "_circle" "3196.079,890.7" "0.15")
(command "_circle" "3197.954,892.7" "0.075")
(command "_circle" "3197.579,892.7" "0.075")
(command "_circle" "3197.204,892.7" "0.075")
(command "_circle" "3196.829,892.7" "0.15")
(command "_circle" "3196.454,892.7" "0.15")
(command "_circle" "3196.079,892.7" "0.15")
(command "_circle" "3197.954,894.7" "0.075")
(command "_circle" "3197.579,894.7" "0.15")
(command "_circle" "3197.204,894.7" "0.075")
(command "_circle" "3196.829,894.7" "0.15")
(command "_circle" "3196.454,894.7" "0.15")
(command "_circle" "3196.079,894.7" "0.15")
(command "_circle" "3197.954,896.7" "0.075")
(command "_circle" "3197.579,896.7" "0.075")
(command "_circle" "3197.204,896.7" "0.15")
(command "_circle" "3196.829,896.7" "0.15")
(command "_circle" "3196.454,896.7" "0.15")
(command "_circle" "3196.079,896.7" "0.15")
(command "_circle" "3197.954,898.7" "0.075")
(command "_circle" "3197.579,898.7" "0.15")
(command "_circle" "3197.204,898.7" "0.15")
(command "_circle" "3196.829,898.7" "0.15")
(command "_circle" "3196.454,898.7" "0.15")
(command "_circle" "3196.079,898.7" "0.15")
(command "_circle" "3197.954,900.7" "0.075")
(command "_circle" "3197.579,900.7" "0.075")
(command "_circle" "3197.204,900.7" "0.075")
(command "_circle" "3196.829,900.7" "0.075")
(command "_circle" "3196.454,900.7" "0.075")
(command "_circle" "3196.079,900.7" "0.075")
(command "_circle" "3195.704,900.7" "0.15")
(command "_circle" "3197.954,902.7" "0.075")
(command "_circle" "3197.579,902.7" "0.15")
(command "_circle" "3197.204,902.7" "0.075")
(command "_circle" "3196.829,902.7" "0.075")
(command "_circle" "3196.454,902.7" "0.075")
(command "_circle" "3196.079,902.7" "0.075")
(command "_circle" "3195.704,902.7" "0.15")
(command "_circle" "3197.954,904.7" "0.075")
(command "_circle" "3197.579,904.7" "0.075")
(command "_circle" "3197.204,904.7" "0.15")
(command "_circle" "3196.829,904.7" "0.075")
(command "_circle" "3196.454,904.7" "0.075")
(command "_circle" "3196.079,904.7" "0.075")
(command "_circle" "3195.704,904.7" "0.15")
(command "_circle" "3197.954,906.7" "0.075")
(command "_circle" "3197.579,906.7" "0.15")
(command "_circle" "3197.204,906.7" "0.15")
(command "_circle" "3196.829,906.7" "0.075")
(command "_circle" "3196.454,906.7" "0.075")
(command "_circle" "3196.079,906.7" "0.075")
(command "_circle" "3195.704,906.7" "0.15")
(command "_circle" "3197.954,908.7" "0.075")
(command "_circle" "3197.579,908.7" "0.075")
(command "_circle" "3197.204,908.7" "0.075")
(command "_circle" "3196.829,908.7" "0.15")
(command "_circle" "3196.454,908.7" "0.075")
(command "_circle" "3196.079,908.7" "0.075")
(command "_circle" "3195.704,908.7" "0.15")
(command "_circle" "3197.954,910.7" "0.075")
(command "_circle" "3197.579,910.7" "0.15")
(command "_circle" "3197.204,910.7" "0.075")
(command "_circle" "3196.829,910.7" "0.15")
(command "_circle" "3196.454,910.7" "0.075")
(command "_circle" "3196.079,910.7" "0.075")
(command "_circle" "3195.704,910.7" "0.15")
(command "_circle" "3197.954,912.7" "0.075")
(command "_circle" "3197.579,912.7" "0.075")
(command "_circle" "3197.204,912.7" "0.15")
(command "_circle" "3196.829,912.7" "0.15")
(command "_circle" "3196.454,912.7" "0.075")
(command "_circle" "3196.079,912.7" "0.075")
(command "_circle" "3195.704,912.7" "0.15")
(command "_circle" "3197.954,914.7" "0.075")
(command "_circle" "3197.579,914.7" "0.15")
(command "_circle" "3197.204,914.7" "0.15")
(command "_circle" "3196.829,914.7" "0.15")
(command "_circle" "3196.454,914.7" "0.075")
(command "_circle" "3196.079,914.7" "0.075")
(command "_circle" "3195.704,914.7" "0.15")
(command "_circle" "3197.954,916.7" "0.075")
(command "_circle" "3197.579,916.7" "0.075")
(command "_circle" "3197.204,916.7" "0.075")
(command "_circle" "3196.829,916.7" "0.075")
(command "_circle" "3196.454,916.7" "0.15")
(command "_circle" "3196.079,916.7" "0.075")
(command "_circle" "3195.704,916.7" "0.15")
(command "_circle" "3197.954,918.7" "0.075")
(command "_circle" "3197.579,918.7" "0.15")
(command "_circle" "3197.204,918.7" "0.075")
(command "_circle" "3196.829,918.7" "0.075")
(command "_circle" "3196.454,918.7" "0.15")
(command "_circle" "3196.079,918.7" "0.075")
(command "_circle" "3195.704,918.7" "0.15")
(command "_circle" "3197.954,920.7" "0.075")
(command "_circle" "3197.579,920.7" "0.075")
(command "_circle" "3197.204,920.7" "0.15")
(command "_circle" "3196.829,920.7" "0.075")
(command "_circle" "3196.454,920.7" "0.15")
(command "_circle" "3196.079,920.7" "0.075")
(command "_circle" "3195.704,920.7" "0.15")
(command "_circle" "3197.954,922.7" "0.075")
(command "_circle" "3197.579,922.7" "0.15")
(command "_circle" "3197.204,922.7" "0.15")
(command "_circle" "3196.829,922.7" "0.075")
(command "_circle" "3196.454,922.7" "0.15")
(command "_circle" "3196.079,922.7" "0.075")
(command "_circle" "3195.704,922.7" "0.15")
(command "_circle" "3197.954,924.7" "0.075")
(command "_circle" "3197.579,924.7" "0.075")
(command "_circle" "3197.204,924.7" "0.075")
(command "_circle" "3196.829,924.7" "0.15")
(command "_circle" "3196.454,924.7" "0.15")
(command "_circle" "3196.079,924.7" "0.075")
(command "_circle" "3195.704,924.7" "0.15")
(command "_circle" "3197.954,926.7" "0.075")
(command "_circle" "3197.579,926.7" "0.15")
(command "_circle" "3197.204,926.7" "0.075")
(command "_circle" "3196.829,926.7" "0.15")
(command "_circle" "3196.454,926.7" "0.15")
(command "_circle" "3196.079,926.7" "0.075")
(command "_circle" "3195.704,926.7" "0.15")
(command "_circle" "3197.954,928.7" "0.075")
(command "_circle" "3197.579,928.7" "0.075")
(command "_circle" "3197.204,928.7" "0.15")
(command "_circle" "3196.829,928.7" "0.15")
(command "_circle" "3196.454,928.7" "0.15")
(command "_circle" "3196.079,928.7" "0.075")
(command "_circle" "3195.704,928.7" "0.15")
(command "_circle" "3197.954,930.7" "0.075")
(command "_circle" "3197.579,930.7" "0.15")
(command "_circle" "3197.204,930.7" "0.15")
(command "_circle" "3196.829,930.7" "0.15")
(command "_circle" "3196.454,930.7" "0.15")
(command "_circle" "3196.079,930.7" "0.075")
(command "_circle" "3195.704,930.7" "0.15")
(command "_circle" "3197.954,932.7" "0.075")
(command "_circle" "3197.579,932.7" "0.075")
(command "_circle" "3197.204,932.7" "0.075")
(command "_circle" "3196.829,932.7" "0.075")
(command "_circle" "3196.454,932.7" "0.075")
(command "_circle" "3196.079,932.7" "0.15")
(command "_circle" "3195.704,932.7" "0.15")
(command "_circle" "3197.954,934.7" "0.075")
(command "_circle" "3197.579,934.7" "0.15")
(command "_circle" "3197.204,934.7" "0.075")
(command "_circle" "3196.829,934.7" "0.075")
(command "_circle" "3196.454,934.7" "0.075")
(command "_circle" "3196.079,934.7" "0.15")
(command "_circle" "3195.704,934.7" "0.15")
(command "_circle" "3197.954,936.7" "0.075")
(command "_circle" "3197.579,936.7" "0.075")
(command "_circle" "3197.204,936.7" "0.15")
(command "_circle" "3196.829,936.7" "0.075")
(command "_circle" "3196.454,936.7" "0.075")
(command "_circle" "3196.079,936.7" "0.15")
(command "_circle" "3195.704,936.7" "0.15")
(command "_circle" "3197.954,938.7" "0.075")
(command "_circle" "3197.579,938.7" "0.15")
(command "_circle" "3197.204,938.7" "0.15")
(command "_circle" "3196.829,938.7" "0.075")
(command "_circle" "3196.454,938.7" "0.075")
(command "_circle" "3196.079,938.7" "0.15")
(command "_circle" "3195.704,938.7" "0.15")
(command "_circle" "3197.954,940.7" "0.075")
(command "_circle" "3197.579,940.7" "0.075")
(command "_circle" "3197.204,940.7" "0.075")
(command "_circle" "3196.829,940.7" "0.15")
(command "_circle" "3196.454,940.7" "0.075")
(command "_circle" "3196.079,940.7" "0.15")
(command "_circle" "3195.704,940.7" "0.15")
(command "_circle" "3197.954,942.7" "0.075")
(command "_circle" "3197.579,942.7" "0.15")
(command "_circle" "3197.204,942.7" "0.075")
(command "_circle" "3196.829,942.7" "0.15")
(command "_circle" "3196.454,942.7" "0.075")
(command "_circle" "3196.079,942.7" "0.15")
(command "_circle" "3195.704,942.7" "0.15")
(command "_circle" "3197.954,944.7" "0.075")
(command "_circle" "3197.579,944.7" "0.075")
(command "_circle" "3197.204,944.7" "0.15")
(command "_circle" "3196.829,944.7" "0.15")
(command "_circle" "3196.454,944.7" "0.075")
(command "_circle" "3196.079,944.7" "0.15")
(command "_circle" "3195.704,944.7" "0.15")
(command "_circle" "3197.954,946.7" "0.075")
(command "_circle" "3197.579,946.7" "0.15")
(command "_circle" "3197.204,946.7" "0.15")
(command "_circle" "3196.829,946.7" "0.15")
(command "_circle" "3196.454,946.7" "0.075")
(command "_circle" "3196.079,946.7" "0.15")
(command "_circle" "3195.704,946.7" "0.15")
(command "_circle" "3197.954,948.7" "0.075")
(command "_circle" "3197.579,948.7" "0.075")
(command "_circle" "3197.204,948.7" "0.075")
(command "_circle" "3196.829,948.7" "0.075")
(command "_circle" "3196.454,948.7" "0.15")
(command "_circle" "3196.079,948.7" "0.15")
(command "_circle" "3195.704,948.7" "0.15")
(command "_circle" "3197.954,950.7" "0.075")
(command "_circle" "3197.579,950.7" "0.15")
(command "_circle" "3197.204,950.7" "0.075")
(command "_circle" "3196.829,950.7" "0.075")
(command "_circle" "3196.454,950.7" "0.15")
(command "_circle" "3196.079,950.7" "0.15")
(command "_circle" "3195.704,950.7" "0.15")
(command "_circle" "3197.954,952.7" "0.075")
(command "_circle" "3197.579,952.7" "0.075")
(command "_circle" "3197.204,952.7" "0.15")
(command "_circle" "3196.829,952.7" "0.075")
(command "_circle" "3196.454,952.7" "0.15")
(command "_circle" "3196.079,952.7" "0.15")
(command "_circle" "3195.704,952.7" "0.15")
(command "_circle" "3197.954,954.7" "0.075")
(command "_circle" "3197.579,954.7" "0.15")
(command "_circle" "3197.204,954.7" "0.15")
(command "_circle" "3196.829,954.7" "0.075")
(command "_circle" "3196.454,954.7" "0.15")
(command "_circle" "3196.079,954.7" "0.15")
(command "_circle" "3195.704,954.7" "0.15")
(command "_circle" "3197.954,956.7" "0.075")
(command "_circle" "3197.579,956.7" "0.075")
(command "_circle" "3197.204,956.7" "0.075")
(command "_circle" "3196.829,956.7" "0.15")
(command "_circle" "3196.454,956.7" "0.15")
(command "_circle" "3196.079,956.7" "0.15")
(command "_circle" "3195.704,956.7" "0.15")
(command "_circle" "3197.954,958.7" "0.075")
(command "_circle" "3197.579,958.7" "0.15")
(command "_circle" "3197.204,958.7" "0.075")
(command "_circle" "3196.829,958.7" "0.15")
(command "_circle" "3196.454,958.7" "0.15")
(command "_circle" "3196.079,958.7" "0.15")
(command "_circle" "3195.704,958.7" "0.15")
(command "_circle" "3197.954,960.7" "0.075")
(command "_circle" "3197.579,960.7" "0.075")
(command "_circle" "3197.204,960.7" "0.15")
(command "_circle" "3196.829,960.7" "0.15")
(command "_circle" "3196.454,960.7" "0.15")
(command "_circle" "3196.079,960.7" "0.15")
(command "_circle" "3195.704,960.7" "0.15")
(command "_circle" "3197.954,962.7" "0.075")
(command "_circle" "3197.579,962.7" "0.15")
(command "_circle" "3197.204,962.7" "0.15")
(command "_circle" "3196.829,962.7" "0.15")
(command "_circle" "3196.454,962.7" "0.15")
(command "_circle" "3196.079,962.7" "0.15")
(command "_circle" "3195.704,962.7" "0.15")
(command "_layer" "set" "nitride" "")
(command "_layer" "set" "text" "")
(command-s "_text" "3186.904,963.3" "2" "-90" "a = 370 nm" )
(sssetfirst nil (ssget "_L"))
(if (not (numberp (vl-string-search "Mac" (getvar "platform")))) (c:txtexp))
(command "_layer" "set" "nitride" "")
(command "_layer" "set" "text" "")
(command-s "_text" "3183.904,963.3" "2" "-90" "gap = 270 nm" )
(sssetfirst nil (ssget "_L"))
(if (not (numberp (vl-string-search "Mac" (getvar "platform")))) (c:txtexp))
(command "_layer" "set" "nitride" "")
(command "_layer" "set" "text" "")
(command-s "_text" "3180.904,963.3" "2" "-90" "amplitude = 127 nm" )
(sssetfirst nil (ssget "_L"))
(if (not (numberp (vl-string-search "Mac" (getvar "platform")))) (c:txtexp))
(command "_layer" "set" "nitride" "")
(command "_layer" "set" "text" "")
(command-s "_text" "3177.904,963.3" "2" "-90" "start width = 280 nm" )
(sssetfirst nil (ssget "_L"))
(if (not (numberp (vl-string-search "Mac" (getvar "platform")))) (c:txtexp))
(command "_layer" "set" "nitride" "")
(command "_layer" "set" "text" "")
(command-s "_text" "3174.904,963.3" "2" "-90" "width = 286 nm" )
(sssetfirst nil (ssget "_L"))
(if (not (numberp (vl-string-search "Mac" (getvar "platform")))) (c:txtexp))
(command "_layer" "set" "nitride" "")
(command "_layer" "set" "text" "")
(command-s "_text" "3171.904,963.3" "2" "-90" "taper: 15" )
(sssetfirst nil (ssget "_L"))
(if (not (numberp (vl-string-search "Mac" (getvar "platform")))) (c:txtexp))
(command "_layer" "set" "nitride" "")
(command "_layer" "set" "text" "")
(command-s "_text" "3168.904,963.3" "2" "-90" "nominal: 150" )
(sssetfirst nil (ssget "_L"))
(if (not (numberp (vl-string-search "Mac" (getvar "platform")))) (c:txtexp))
(command "_layer" "set" "nitride" "")
(command "_layer" "set" "indicators" "")
(setq coords (list 
(list 3120.415 940) 
(list 3120.415 920) 
(list 3100.415 900) 
(list 3120.415 880) 
(list 3120.415 860) 
(list 3120.415 900) 
(list 3120.415 887.0711) 
(list 3107.4861 900) 
(list 3120.415 912.9289) 
(list 3120.415 900)))
(apply 'command (append '("pline") coords '("c")))
(command "._fillet" "radius" "1" "._fillet" "P" (entlast))
(setq coords (list 
(list 3279.585 940) 
(list 3279.585 920) 
(list 3299.585 900) 
(list 3279.585 880) 
(list 3279.585 860) 
(list 3279.585 900) 
(list 3279.585 887.0711) 
(list 3292.5139 900) 
(list 3279.585 912.9289) 
(list 3279.585 900)))
(apply 'command (append '("pline") coords '("c")))
(command "._fillet" "radius" "1" "._fillet" "P" (entlast))
(command "_layer" "set" "holes" "")
(command "_circle" "3118.0629,914.1124" "0.5")
(command "_circle" "3115.7109,911.7603" "0.5")
(command "_circle" "3113.3588,909.4083" "0.5")
(command "_circle" "3111.0067,907.0562" "0.5")
(command "_circle" "3108.6547,904.7041" "0.5")
(command "_circle" "3106.3026,902.3521" "0.5")
(command "_circle" "3103.9505,900" "0.5")
(command "_circle" "3106.3026,897.6479" "0.5")
(command "_circle" "3108.6547,895.2959" "0.5")
(command "_circle" "3111.0067,892.9438" "0.5")
(command "_circle" "3113.3588,890.5917" "0.5")
(command "_circle" "3115.7109,888.2397" "0.5")
(command "_circle" "3118.0629,885.8876" "0.5")
(command "_circle" "3281.9371,914.1124" "0.5")
(command "_circle" "3284.2891,911.7603" "0.5")
(command "_circle" "3286.6412,909.4083" "0.5")
(command "_circle" "3288.9933,907.0562" "0.5")
(command "_circle" "3291.3453,904.7041" "0.5")
(command "_circle" "3293.6974,902.3521" "0.5")
(command "_circle" "3296.0495,900" "0.5")
(command "_circle" "3293.6974,897.6479" "0.5")
(command "_circle" "3291.3453,895.2959" "0.5")
(command "_circle" "3288.9933,892.9438" "0.5")
(command "_circle" "3286.6412,890.5917" "0.5")
(command "_circle" "3284.2891,888.2397" "0.5")
(command "_circle" "3281.9371,885.8876" "0.5")
(command "_layer" "set" "nitride" "")
(command "_block" "blkcoupler10" "3200,900" coupler10 "")
(command "_insert" "blkcoupler10" "3200,900" "1" "1" "0")
(command "_insert" "blkcoupler10" "3200,900" "1" "1" "180")
(command "_block" "blksinglenanobeam10" "3200,900" singlenanobeam10 "")
(command "_insert" "blksinglenanobeam10" "3200,900" "1" "1" "0")
(command "_insert" "blksinglenanobeam10" "3200,900" "1" "1" "180")
(command "_block" "blkanglednodearray10" "3200,900" anglednodearray10 "")
(command "_insert" "blkanglednodearray10" "3200,900" "1" "1" "0")
(command "_insert" "blkanglednodearray10" "3200,900" "1" "1" "180")
(command "_block" "blkcooledsinglenanobeam10" "3200,900" cooledsinglenanobeam10 "")
(command "_insert" "blkcooledsinglenanobeam10" "3200,900" "1" "1" "0")
(command "_insert" "blkcooledsinglenanobeam10" "3200,900" "1" "1" "180")
(command "_block" "blkyjunction10" "3200,900" yjunction10 "")
(command "_insert" "blkyjunction10" "3200,900" "1" "1" "0")
(command "_insert" "blkyjunction10" "3200,900" "1" "1" "180")
; DRAWING BULGING VEE GROOVE
(command "_layer" "set" "vgroove" "")
(setq coords (list 
(list 3125.415 -605) 
(list 3125.415 0) 
(list 3125.415 0) 
(list 3125.415 1800) 
(list 3125.415 1800) 
(list 3125.415 2405) 
(list 3274.585 2405) 
(list 3274.585 1800) 
(list 3274.585 1800) 
(list 3274.585 0) 
(list 3274.585 0) 
(list 3274.585 -605)))
(apply 'command (append '("pline") coords '("c")))
(command "._fillet" "radius" "0" "._fillet" "P" (entlast))
(command "_layer" "set" "window" "")
(command "_rectangle" "3125.415,-1935" "3274.585,-600")
(command "_rectangle" "3125.415,2400" "3274.585,5300")
(command "_layer" "set" "grid" "")
(command "_rectangle" "3126.415,-1934" "3149.9433,-1909.2133")
(command "_array" "last" "" "R" "75" "3" "25.7867" "24.5283")
(command "_rectangle" "3201,-1934" "3224.5283,-1909.2133")
(command "_array" "last" "" "R" "75" "3" "25.7867" "24.5283")
(command "_rectangle" "3126.415,1" "3149.9433,25.7")
(command "_array" "last" "" "R" "70" "3" "25.7" "24.5283")
(command "_rectangle" "3201,1" "3224.5283,25.7")
(command "_array" "last" "" "R" "70" "3" "25.7" "24.5283")
(command "_rectangle" "3126.415,1801" "3149.9433,1825.9185")
(command "_array" "last" "" "R" "135" "3" "25.9185" "24.5283")
(command "_rectangle" "3201,1801" "3224.5283,1825.9185")
(command "_array" "last" "" "R" "135" "3" "25.9185" "24.5283")
(command "_layer" "set" "vgrooveFDA" "")
(command "_rectangle" "3274.585,-2233" "3125.415,-1933")
(command "_layer" "set" "nitride" "")
(command "_layer" "set" "holes" "")
(command "_circle" "3277.085,331.5" "0.5")
(command "_array" "last" "" "R" "379" "1" "3" "2.5")
(command "_circle" "3122.915,331.5" "0.5")
(command "_array" "last" "" "R" "379" "1" "3" "-2.5")
(command "_layer" "set" "nitride" "")
(command "_layer" "set" "window" "")
(command "_layer" "set" "window" "")
(command "_rectangle" "3279.585,0" "3440.415,1800")
(command "._fillet" "radius" "20" "._fillet" "P" (entlast))
(command "_layer" "set" "grid" "")
(command "_rectangle" "3280.585,1" "3302.4179,25.7")
(command "_array" "last" "" "R" "70" "7" "25.7" "22.8329")
(command "_layer" "set" "nitride" "")
; DRAWING REGION LAYER
(command "_layer" "set" "regionLayer10" "")
(command "_rectangle" "3120,-460" "3280,2260")
(command "_layer" "set" "nitride" "")
(setq coupler10 nil)
(setq singlenanobeam10 nil)
(setq anglednodearray10 nil)
(setq cooledsinglenanobeam10 nil)
(setq yjunction10 nil)
; DEVICE #11
(command "_layer" "set" "window" "")
(command "_circle" "3432.915,-415" "5")
(command "_circle" "3432.915,-402.5" "5")
(command "_circle" "3432.915,-390" "5")
(command "_circle" "3432.915,-377.5" "5")
(command "_circle" "3420.415,-415" "5")
(command "_circle" "3420.415,-402.5" "5")
(command "_circle" "3420.415,-390" "5")
(command "_circle" "3420.415,-377.5" "5")
(command "_circle" "3407.915,-415" "5")
(command "_circle" "3407.915,-402.5" "5")
(command "_circle" "3407.915,-390" "5")
(command "_layer" "set" "nitride" "")
(setq currobj nil)
(setq currobj (ssadd))
; DRAWING COUPLER
(setq coords (list 
(list 3520.0615 -415) 
(list 3520.0615 -413) 
(list 3593.585 -413) 
(list 3593.585 -413) 
(list 3593.9677 -413.0761) 
(list 3594.2921 -413.2929) 
(list 3594.5089 -413.6173) 
(list 3594.585 -414) 
(list 3594.585 -411.8) 
(list 3594.585 -411.8) 
(list 3594.5089 -412.1827) 
(list 3594.2921 -412.5071) 
(list 3593.9677 -412.7239) 
(list 3593.585 -412.8) 
(list 3520.0615 -412.8) 
(list 3520.0615 -410.8) 
(list 3519.9385 -410.8) 
(list 3519.9385 -412.8) 
(list 3446.415 -412.8) 
(list 3446.0323 -412.7239) 
(list 3445.7079 -412.5071) 
(list 3445.4911 -412.1827) 
(list 3445.415 -411.8) 
(list 3445.415 -411.8) 
(list 3445.415 -414) 
(list 3445.4911 -413.6173) 
(list 3445.7079 -413.2929) 
(list 3446.0323 -413.0761) 
(list 3446.415 -413) 
(list 3446.415 -413) 
(list 3519.9385 -413) 
(list 3519.9385 -415)))
(apply 'command (append '("pline") coords '("c")))
(setq currobj (ssadd (entlast) currobj))
(command "._fillet" "radius" "0.3" "._fillet" "P" (entlast))
(command "_layer" "set" "holes" "")
(command "_circle" "3520,-412.9" "0.113")
(setq currobj (ssadd (entlast) currobj))
(command "_layer" "set" "nitride" "")
(command "_layer" "set" "text" "")
(command "_circle" "3519.2,-415" "0.075")
(command "_circle" "3519.2,-414.7" "0.075")
(command "_circle" "3519.2,-414.4" "0.075")
(command "_circle" "3518.9,-415" "0.075")
(command "_circle" "3518.9,-414.7" "0.075")
(command "_circle" "3518.9,-414.4" "0.075")
(command "_circle" "3518.6,-415" "0.075")
(command "_circle" "3518.6,-414.7" "0.075")
(command "_circle" "3518.6,-414.4" "0.075")
(command "_layer" "set" "nitride" "")
(command "_layer" "set" "prebias" "")
(command "_rectangle" "3445.415,-414" "3594.585,-411.8")
(setq currobj (ssadd (entlast) currobj))
(command "_rectangle" "3519.9385,-415" "3520.0615,-410.8")
(setq currobj (ssadd (entlast) currobj))
(command "_layer" "set" "nitride" "")
(setq coupler11 currobj)
(setq currobj nil)
(setq currobj (ssadd))
; DRAWING SINGLE NANOBEAM
(setq coords (list 
(list 3520.0615 -410.8) 
(list 3520.0615 -409.1417) 
(list 3520.0615 -407.4833) 
(list 3520.0615 -405.825) 
(list 3520.0615 -404.1667) 
(list 3520.0615 -402.5083) 
(list 3520.0615 -400.85) 
(list 3520.0615 -399.1917) 
(list 3520.0615 -397.5333) 
(list 3520.0616 -395.875) 
(list 3520.0616 -394.2167) 
(list 3520.0616 -392.5583) 
(list 3520.0616 -390.9) 
(list 3520.0617 -389.2417) 
(list 3520.0617 -387.5833) 
(list 3520.0617 -385.925) 
(list 3520.0618 -384.2667) 
(list 3520.0619 -382.6083) 
(list 3520.0619 -380.95) 
(list 3520.062 -379.2917) 
(list 3520.0621 -377.6333) 
(list 3520.0622 -375.975) 
(list 3520.0623 -374.3167) 
(list 3520.0624 -372.6583) 
(list 3520.0625 -371) 
(list 3520.0626 -369.3417) 
(list 3520.0628 -367.6833) 
(list 3520.0629 -366.025) 
(list 3520.0631 -364.3667) 
(list 3520.0632 -362.7083) 
(list 3520.0634 -361.05) 
(list 3520.0636 -359.3917) 
(list 3520.0638 -357.7333) 
(list 3520.0641 -356.075) 
(list 3520.0643 -354.4167) 
(list 3520.0646 -352.7583) 
(list 3520.0648 -351.1) 
(list 3520.0651 -349.4417) 
(list 3520.0654 -347.7833) 
(list 3520.0657 -346.125) 
(list 3520.0661 -344.4667) 
(list 3520.0664 -342.8083) 
(list 3520.0668 -341.15) 
(list 3520.0672 -339.4917) 
(list 3520.0676 -337.8333) 
(list 3520.068 -336.175) 
(list 3520.0685 -334.5167) 
(list 3520.0689 -332.8583) 
(list 3520.0694 -331.2) 
(list 3520.0699 -329.5417) 
(list 3520.0704 -327.8833) 
(list 3520.071 -326.225) 
(list 3520.0715 -324.5667) 
(list 3520.0721 -322.9083) 
(list 3520.0728 -321.25) 
(list 3520.0734 -319.5917) 
(list 3520.0741 -317.9333) 
(list 3520.0747 -316.275) 
(list 3520.0754 -314.6167) 
(list 3520.0762 -312.9583) 
(list 3520.0769 -311.3) 
(list 3520.0777 -309.6417) 
(list 3520.0785 -307.9833) 
(list 3520.0794 -306.325) 
(list 3520.0802 -304.6667) 
(list 3520.0811 -303.0083) 
(list 3520.082 -301.35) 
(list 3520.083 -299.6917) 
(list 3520.084 -298.0333) 
(list 3520.085 -296.375) 
(list 3520.086 -294.7167) 
(list 3520.0871 -293.0583) 
(list 3520.0882 -291.4) 
(list 3520.0893 -289.7417) 
(list 3520.0905 -288.0833) 
(list 3520.0917 -286.425) 
(list 3520.0929 -284.7667) 
(list 3520.0941 -283.1083) 
(list 3520.0954 -281.45) 
(list 3520.0967 -279.7917) 
(list 3520.0981 -278.1333) 
(list 3520.0995 -276.475) 
(list 3520.1009 -274.8167) 
(list 3520.1024 -273.1583) 
(list 3520.1039 -271.5) 
(list 3520.1054 -269.8417) 
(list 3520.107 -268.1833) 
(list 3520.1086 -266.525) 
(list 3520.1102 -264.8667) 
(list 3520.1119 -263.2083) 
(list 3520.1136 -261.55) 
(list 3520.1154 -259.8917) 
(list 3520.1172 -258.2333) 
(list 3520.119 -256.575) 
(list 3520.1209 -254.9167) 
(list 3520.1228 -253.2583) 
(list 3520.1247 -251.6) 
(list 3520.1267 -249.9417) 
(list 3520.1288 -248.2833) 
(list 3520.1308 -246.625) 
(list 3520.133 -244.9667) 
(list 3520.1351 -243.3083) 
(list 3520.1373 -241.65) 
(list 3520.1396 -239.9917) 
(list 3520.1419 -238.3333) 
(list 3520.1442 -236.675) 
(list 3520.1466 -235.0167) 
(list 3520.1491 -233.3583) 
(list 3520.1515 -231.7) 
(list 3520.1541 -230.0417) 
(list 3520.1566 -228.3833) 
(list 3520.1592 -226.725) 
(list 3520.1619 -225.0667) 
(list 3520.1646 -223.4083) 
(list 3520.1674 -221.75) 
(list 3520.1702 -220.0917) 
(list 3520.1731 -218.4333) 
(list 3520.176 -216.775) 
(list 3520.1789 -215.1167) 
(list 3520.1819 -213.4583) 
(list 3520.185 -211.8) 
(list 3519.815 -211.8) 
(list 3519.8181 -213.4583) 
(list 3519.8211 -215.1167) 
(list 3519.824 -216.775) 
(list 3519.8269 -218.4333) 
(list 3519.8298 -220.0917) 
(list 3519.8326 -221.75) 
(list 3519.8354 -223.4083) 
(list 3519.8381 -225.0667) 
(list 3519.8408 -226.725) 
(list 3519.8434 -228.3833) 
(list 3519.8459 -230.0417) 
(list 3519.8485 -231.7) 
(list 3519.8509 -233.3583) 
(list 3519.8534 -235.0167) 
(list 3519.8558 -236.675) 
(list 3519.8581 -238.3333) 
(list 3519.8604 -239.9917) 
(list 3519.8627 -241.65) 
(list 3519.8649 -243.3083) 
(list 3519.867 -244.9667) 
(list 3519.8692 -246.625) 
(list 3519.8712 -248.2833) 
(list 3519.8733 -249.9417) 
(list 3519.8753 -251.6) 
(list 3519.8772 -253.2583) 
(list 3519.8791 -254.9167) 
(list 3519.881 -256.575) 
(list 3519.8828 -258.2333) 
(list 3519.8846 -259.8917) 
(list 3519.8864 -261.55) 
(list 3519.8881 -263.2083) 
(list 3519.8898 -264.8667) 
(list 3519.8914 -266.525) 
(list 3519.893 -268.1833) 
(list 3519.8946 -269.8417) 
(list 3519.8961 -271.5) 
(list 3519.8976 -273.1583) 
(list 3519.8991 -274.8167) 
(list 3519.9005 -276.475) 
(list 3519.9019 -278.1333) 
(list 3519.9033 -279.7917) 
(list 3519.9046 -281.45) 
(list 3519.9059 -283.1083) 
(list 3519.9071 -284.7667) 
(list 3519.9083 -286.425) 
(list 3519.9095 -288.0833) 
(list 3519.9107 -289.7417) 
(list 3519.9118 -291.4) 
(list 3519.9129 -293.0583) 
(list 3519.914 -294.7167) 
(list 3519.915 -296.375) 
(list 3519.916 -298.0333) 
(list 3519.917 -299.6917) 
(list 3519.918 -301.35) 
(list 3519.9189 -303.0083) 
(list 3519.9198 -304.6667) 
(list 3519.9206 -306.325) 
(list 3519.9215 -307.9833) 
(list 3519.9223 -309.6417) 
(list 3519.9231 -311.3) 
(list 3519.9238 -312.9583) 
(list 3519.9246 -314.6167) 
(list 3519.9253 -316.275) 
(list 3519.9259 -317.9333) 
(list 3519.9266 -319.5917) 
(list 3519.9272 -321.25) 
(list 3519.9279 -322.9083) 
(list 3519.9285 -324.5667) 
(list 3519.929 -326.225) 
(list 3519.9296 -327.8833) 
(list 3519.9301 -329.5417) 
(list 3519.9306 -331.2) 
(list 3519.9311 -332.8583) 
(list 3519.9315 -334.5167) 
(list 3519.932 -336.175) 
(list 3519.9324 -337.8333) 
(list 3519.9328 -339.4917) 
(list 3519.9332 -341.15) 
(list 3519.9336 -342.8083) 
(list 3519.9339 -344.4667) 
(list 3519.9343 -346.125) 
(list 3519.9346 -347.7833) 
(list 3519.9349 -349.4417) 
(list 3519.9352 -351.1) 
(list 3519.9354 -352.7583) 
(list 3519.9357 -354.4167) 
(list 3519.9359 -356.075) 
(list 3519.9362 -357.7333) 
(list 3519.9364 -359.3917) 
(list 3519.9366 -361.05) 
(list 3519.9368 -362.7083) 
(list 3519.9369 -364.3667) 
(list 3519.9371 -366.025) 
(list 3519.9372 -367.6833) 
(list 3519.9374 -369.3417) 
(list 3519.9375 -371) 
(list 3519.9376 -372.6583) 
(list 3519.9377 -374.3167) 
(list 3519.9378 -375.975) 
(list 3519.9379 -377.6333) 
(list 3519.938 -379.2917) 
(list 3519.9381 -380.95) 
(list 3519.9381 -382.6083) 
(list 3519.9382 -384.2667) 
(list 3519.9383 -385.925) 
(list 3519.9383 -387.5833) 
(list 3519.9383 -389.2417) 
(list 3519.9384 -390.9) 
(list 3519.9384 -392.5583) 
(list 3519.9384 -394.2167) 
(list 3519.9384 -395.875) 
(list 3519.9385 -397.5333) 
(list 3519.9385 -399.1917) 
(list 3519.9385 -400.85) 
(list 3519.9385 -402.5083) 
(list 3519.9385 -404.1667) 
(list 3519.9385 -405.825) 
(list 3519.9385 -407.4833) 
(list 3519.9385 -409.1417) 
(list 3519.9385 -410.8)))
(apply 'command (append '("pline") coords '("c")))
(setq currobj (ssadd (entlast) currobj))
(command "_layer" "set" "prebias" "")
(command "_rectangle" "3519.815,-410.8" "3520.185,-211.8")
(setq currobj (ssadd (entlast) currobj))
(command "_layer" "set" "nitride" "")
(setq singlenanobeam11 currobj)
(setq currobj nil)
(setq currobj (ssadd))
; DRAWING NODE ARRAY
(setq coords (list 
(list 3520.185 -211.8) 
(list 3520.5625 -201.8) 
(list 3520.5625 -201.8) 
(list 3520.5625 -200.8) 
(list 3594.585 -212.6864) 
(list 3594.585 -207.7434) 
(list 3520.5625 -197.357) 
(list 3520.5625 -196.357) 
(list 3520.5625 -196.357) 
(list 3520.2625 -186.357) 
(list 3519.7375 -186.357) 
(list 3519.4375 -196.357) 
(list 3519.4375 -196.357) 
(list 3519.4375 -197.357) 
(list 3445.415 -207.7434) 
(list 3445.415 -212.6864) 
(list 3519.4375 -200.8) 
(list 3519.4375 -201.8) 
(list 3519.4375 -201.8) 
(list 3519.815 -211.8)))
(apply 'command (append '("pline") coords '("c")))
(setq currobj (ssadd (entlast) currobj))
(command "_layer" "set" "prebias" "")
(setq coords (list 
(list 3519.4375 -212.6864) 
(list 3519.4375 -200.8) 
(list 3445.415 -212.6864) 
(list 3445.415 -207.7434) 
(list 3519.4375 -197.357) 
(list 3519.4375 -186.357) 
(list 3520.5625 -186.357) 
(list 3520.5625 -197.357) 
(list 3594.585 -207.7434) 
(list 3594.585 -212.6864) 
(list 3520.5625 -200.8) 
(list 3520.5625 -212.6864)))
(apply 'command (append '("pline") coords '("c")))
(setq currobj (ssadd (entlast) currobj))
(command "_layer" "set" "nitride" "")
(command "_layer" "set" "fda1" "")
(setq coords (list 
(list 3520.5625 -200.657) 
(list 3594.585 -212.5434) 
(list 3594.585 -212.3664) 
(list 3520.5625 -200.58)))
(apply 'command (append '("pline") coords '("c")))
(setq currobj (ssadd (entlast) currobj))
(setq coords (list 
(list 3520.5625 -200.437) 
(list 3594.585 -212.2234) 
(list 3594.585 -212.0464) 
(list 3520.5625 -200.36)))
(apply 'command (append '("pline") coords '("c")))
(setq currobj (ssadd (entlast) currobj))
(setq coords (list 
(list 3520.5625 -200.217) 
(list 3594.585 -211.9034) 
(list 3594.585 -211.7264) 
(list 3520.5625 -200.14)))
(apply 'command (append '("pline") coords '("c")))
(setq currobj (ssadd (entlast) currobj))
(setq coords (list 
(list 3520.5625 -199.997) 
(list 3594.585 -211.5834) 
(list 3594.585 -211.4064) 
(list 3520.5625 -199.92)))
(apply 'command (append '("pline") coords '("c")))
(setq currobj (ssadd (entlast) currobj))
(setq coords (list 
(list 3520.5625 -199.777) 
(list 3594.585 -211.2634) 
(list 3594.585 -211.0864) 
(list 3520.5625 -199.7)))
(apply 'command (append '("pline") coords '("c")))
(setq currobj (ssadd (entlast) currobj))
(setq coords (list 
(list 3520.5625 -199.557) 
(list 3594.585 -210.9434) 
(list 3594.585 -210.7664) 
(list 3520.5625 -199.48)))
(apply 'command (append '("pline") coords '("c")))
(setq currobj (ssadd (entlast) currobj))
(setq coords (list 
(list 3520.5625 -199.337) 
(list 3594.585 -210.6234) 
(list 3594.585 -210.4464) 
(list 3520.5625 -199.26)))
(apply 'command (append '("pline") coords '("c")))
(setq currobj (ssadd (entlast) currobj))
(setq coords (list 
(list 3520.5625 -199.117) 
(list 3594.585 -210.3034) 
(list 3594.585 -210.1264) 
(list 3520.5625 -199.04)))
(apply 'command (append '("pline") coords '("c")))
(setq currobj (ssadd (entlast) currobj))
(setq coords (list 
(list 3520.5625 -198.897) 
(list 3594.585 -209.9834) 
(list 3594.585 -209.8064) 
(list 3520.5625 -198.82)))
(apply 'command (append '("pline") coords '("c")))
(setq currobj (ssadd (entlast) currobj))
(setq coords (list 
(list 3520.5625 -198.677) 
(list 3594.585 -209.6634) 
(list 3594.585 -209.4864) 
(list 3520.5625 -198.6)))
(apply 'command (append '("pline") coords '("c")))
(setq currobj (ssadd (entlast) currobj))
(setq coords (list 
(list 3520.5625 -198.457) 
(list 3594.585 -209.3434) 
(list 3594.585 -209.1664) 
(list 3520.5625 -198.38)))
(apply 'command (append '("pline") coords '("c")))
(setq currobj (ssadd (entlast) currobj))
(setq coords (list 
(list 3520.5625 -198.237) 
(list 3594.585 -209.0234) 
(list 3594.585 -208.8464) 
(list 3520.5625 -198.16)))
(apply 'command (append '("pline") coords '("c")))
(setq currobj (ssadd (entlast) currobj))
(setq coords (list 
(list 3520.5625 -198.017) 
(list 3594.585 -208.7034) 
(list 3594.585 -208.5264) 
(list 3520.5625 -197.94)))
(apply 'command (append '("pline") coords '("c")))
(setq currobj (ssadd (entlast) currobj))
(setq coords (list 
(list 3520.5625 -197.797) 
(list 3594.585 -208.3834) 
(list 3594.585 -208.2064) 
(list 3520.5625 -197.72)))
(apply 'command (append '("pline") coords '("c")))
(setq currobj (ssadd (entlast) currobj))
(setq coords (list 
(list 3520.5625 -197.577) 
(list 3594.585 -208.0634) 
(list 3594.585 -207.8864) 
(list 3520.5625 -197.5)))
(apply 'command (append '("pline") coords '("c")))
(setq currobj (ssadd (entlast) currobj))
(setq coords (list 
(list 3519.4375 -197.5) 
(list 3445.415 -207.8864) 
(list 3445.415 -208.0634) 
(list 3519.4375 -197.577)))
(apply 'command (append '("pline") coords '("c")))
(setq currobj (ssadd (entlast) currobj))
(setq coords (list 
(list 3519.4375 -197.72) 
(list 3445.415 -208.2064) 
(list 3445.415 -208.3834) 
(list 3519.4375 -197.797)))
(apply 'command (append '("pline") coords '("c")))
(setq currobj (ssadd (entlast) currobj))
(setq coords (list 
(list 3519.4375 -197.94) 
(list 3445.415 -208.5264) 
(list 3445.415 -208.7034) 
(list 3519.4375 -198.017)))
(apply 'command (append '("pline") coords '("c")))
(setq currobj (ssadd (entlast) currobj))
(setq coords (list 
(list 3519.4375 -198.16) 
(list 3445.415 -208.8464) 
(list 3445.415 -209.0234) 
(list 3519.4375 -198.237)))
(apply 'command (append '("pline") coords '("c")))
(setq currobj (ssadd (entlast) currobj))
(setq coords (list 
(list 3519.4375 -198.38) 
(list 3445.415 -209.1664) 
(list 3445.415 -209.3434) 
(list 3519.4375 -198.457)))
(apply 'command (append '("pline") coords '("c")))
(setq currobj (ssadd (entlast) currobj))
(setq coords (list 
(list 3519.4375 -198.6) 
(list 3445.415 -209.4864) 
(list 3445.415 -209.6634) 
(list 3519.4375 -198.677)))
(apply 'command (append '("pline") coords '("c")))
(setq currobj (ssadd (entlast) currobj))
(setq coords (list 
(list 3519.4375 -198.82) 
(list 3445.415 -209.8064) 
(list 3445.415 -209.9834) 
(list 3519.4375 -198.897)))
(apply 'command (append '("pline") coords '("c")))
(setq currobj (ssadd (entlast) currobj))
(setq coords (list 
(list 3519.4375 -199.04) 
(list 3445.415 -210.1264) 
(list 3445.415 -210.3034) 
(list 3519.4375 -199.117)))
(apply 'command (append '("pline") coords '("c")))
(setq currobj (ssadd (entlast) currobj))
(setq coords (list 
(list 3519.4375 -199.26) 
(list 3445.415 -210.4464) 
(list 3445.415 -210.6234) 
(list 3519.4375 -199.337)))
(apply 'command (append '("pline") coords '("c")))
(setq currobj (ssadd (entlast) currobj))
(setq coords (list 
(list 3519.4375 -199.48) 
(list 3445.415 -210.7664) 
(list 3445.415 -210.9434) 
(list 3519.4375 -199.557)))
(apply 'command (append '("pline") coords '("c")))
(setq currobj (ssadd (entlast) currobj))
(setq coords (list 
(list 3519.4375 -199.7) 
(list 3445.415 -211.0864) 
(list 3445.415 -211.2634) 
(list 3519.4375 -199.777)))
(apply 'command (append '("pline") coords '("c")))
(setq currobj (ssadd (entlast) currobj))
(setq coords (list 
(list 3519.4375 -199.92) 
(list 3445.415 -211.4064) 
(list 3445.415 -211.5834) 
(list 3519.4375 -199.997)))
(apply 'command (append '("pline") coords '("c")))
(setq currobj (ssadd (entlast) currobj))
(setq coords (list 
(list 3519.4375 -200.14) 
(list 3445.415 -211.7264) 
(list 3445.415 -211.9034) 
(list 3519.4375 -200.217)))
(apply 'command (append '("pline") coords '("c")))
(setq currobj (ssadd (entlast) currobj))
(setq coords (list 
(list 3519.4375 -200.36) 
(list 3445.415 -212.0464) 
(list 3445.415 -212.2234) 
(list 3519.4375 -200.437)))
(apply 'command (append '("pline") coords '("c")))
(setq currobj (ssadd (entlast) currobj))
(setq coords (list 
(list 3519.4375 -200.58) 
(list 3445.415 -212.3664) 
(list 3445.415 -212.5434) 
(list 3519.4375 -200.657)))
(apply 'command (append '("pline") coords '("c")))
(setq currobj (ssadd (entlast) currobj))
(command "_layer" "set" "nitride" "")
(command "_layer" "set" "text" "")
(command "_circle" "3518.985,-211.8" "0.075")
(command "_circle" "3518.985,-211.5" "0.075")
(command "_circle" "3518.985,-211.2" "0.075")
(command "_circle" "3518.985,-210.9" "0.075")
(command "_circle" "3518.985,-210.6" "0.075")
(command "_circle" "3518.685,-211.8" "0.075")
(command "_circle" "3518.685,-211.5" "0.075")
(command "_circle" "3518.685,-211.2" "0.075")
(command "_circle" "3518.685,-210.9" "0.075")
(command "_circle" "3518.685,-210.6" "0.075")
(command "_circle" "3518.385,-211.8" "0.075")
(command "_circle" "3518.385,-211.5" "0.075")
(command "_circle" "3518.385,-211.2" "0.075")
(command "_circle" "3518.385,-210.9" "0.075")
(command "_circle" "3518.385,-210.6" "0.075")
(command "_circle" "3518.085,-211.8" "0.075")
(command "_circle" "3518.085,-211.5" "0.075")
(command "_circle" "3518.085,-211.2" "0.075")
(command "_circle" "3518.085,-210.9" "0.075")
(command "_circle" "3518.085,-210.6" "0.075")
(command "_circle" "3517.785,-211.8" "0.075")
(command "_circle" "3517.785,-211.5" "0.075")
(command "_circle" "3517.785,-211.2" "0.075")
(command "_circle" "3517.785,-210.9" "0.075")
(command "_circle" "3517.785,-210.6" "0.075")
(command "_layer" "set" "nitride" "")
(setq anglednodearray11 currobj)
(setq currobj nil)
(setq currobj (ssadd))
; DRAWING COOLED SINGLE NANOBEAM
(setq coords (list 
(list 3520.2625 -186.357) 
(list 3520.2625 -181.357) 
(list 3519.7375 -181.357) 
(list 3519.7375 -186.357)))
(apply 'command (append '("pline") coords '("c")))
(setq currobj (ssadd (entlast) currobj))
(command "_layer" "set" "prebias" "")
(command "_rectangle" "3519.7375,-186.357" "3520.2625,-181.357")
(setq currobj (ssadd (entlast) currobj))
(command "_layer" "set" "nitride" "")
(setq coords (list 
(list 3520.2625 -181.357) 
(list 3520.5625 -171.357) 
(list 3520.5625 -171.357) 
(list 3520.5625 -170.357) 
(list 3594.585 -171.107) 
(list 3594.585 -166.164) 
(list 3520.5625 -166.914) 
(list 3520.5625 -165.914) 
(list 3520.5625 -165.914) 
(list 3520.2625 -155.914) 
(list 3519.7375 -155.914) 
(list 3519.4375 -165.914) 
(list 3519.4375 -165.914) 
(list 3519.4375 -166.914) 
(list 3445.415 -166.164) 
(list 3445.415 -171.107) 
(list 3519.4375 -170.357) 
(list 3519.4375 -171.357) 
(list 3519.4375 -171.357) 
(list 3519.7375 -181.357)))
(apply 'command (append '("pline") coords '("c")))
(setq currobj (ssadd (entlast) currobj))
(command "_layer" "set" "prebias" "")
(setq coords (list 
(list 3519.4375 -181.357) 
(list 3519.4375 -170.357) 
(list 3445.415 -171.107) 
(list 3445.415 -166.164) 
(list 3519.4375 -166.914) 
(list 3519.4375 -155.914) 
(list 3520.5625 -155.914) 
(list 3520.5625 -166.914) 
(list 3594.585 -166.164) 
(list 3594.585 -171.107) 
(list 3520.5625 -170.357) 
(list 3520.5625 -181.357)))
(apply 'command (append '("pline") coords '("c")))
(setq currobj (ssadd (entlast) currobj))
(command "_layer" "set" "nitride" "")
(command "_layer" "set" "fda1" "")
(setq coords (list 
(list 3520.5625 -170.214) 
(list 3594.585 -170.964) 
(list 3594.585 -170.787) 
(list 3520.5625 -170.137)))
(apply 'command (append '("pline") coords '("c")))
(setq currobj (ssadd (entlast) currobj))
(setq coords (list 
(list 3520.5625 -169.994) 
(list 3594.585 -170.644) 
(list 3594.585 -170.467) 
(list 3520.5625 -169.917)))
(apply 'command (append '("pline") coords '("c")))
(setq currobj (ssadd (entlast) currobj))
(setq coords (list 
(list 3520.5625 -169.774) 
(list 3594.585 -170.324) 
(list 3594.585 -170.147) 
(list 3520.5625 -169.697)))
(apply 'command (append '("pline") coords '("c")))
(setq currobj (ssadd (entlast) currobj))
(setq coords (list 
(list 3520.5625 -169.554) 
(list 3594.585 -170.004) 
(list 3594.585 -169.827) 
(list 3520.5625 -169.477)))
(apply 'command (append '("pline") coords '("c")))
(setq currobj (ssadd (entlast) currobj))
(setq coords (list 
(list 3520.5625 -169.334) 
(list 3594.585 -169.684) 
(list 3594.585 -169.507) 
(list 3520.5625 -169.257)))
(apply 'command (append '("pline") coords '("c")))
(setq currobj (ssadd (entlast) currobj))
(setq coords (list 
(list 3520.5625 -169.114) 
(list 3594.585 -169.364) 
(list 3594.585 -169.187) 
(list 3520.5625 -169.037)))
(apply 'command (append '("pline") coords '("c")))
(setq currobj (ssadd (entlast) currobj))
(setq coords (list 
(list 3520.5625 -168.894) 
(list 3594.585 -169.044) 
(list 3594.585 -168.867) 
(list 3520.5625 -168.817)))
(apply 'command (append '("pline") coords '("c")))
(setq currobj (ssadd (entlast) currobj))
(setq coords (list 
(list 3520.5625 -168.674) 
(list 3594.585 -168.724) 
(list 3594.585 -168.547) 
(list 3520.5625 -168.597)))
(apply 'command (append '("pline") coords '("c")))
(setq currobj (ssadd (entlast) currobj))
(setq coords (list 
(list 3520.5625 -168.454) 
(list 3594.585 -168.404) 
(list 3594.585 -168.227) 
(list 3520.5625 -168.377)))
(apply 'command (append '("pline") coords '("c")))
(setq currobj (ssadd (entlast) currobj))
(setq coords (list 
(list 3520.5625 -168.234) 
(list 3594.585 -168.084) 
(list 3594.585 -167.907) 
(list 3520.5625 -168.157)))
(apply 'command (append '("pline") coords '("c")))
(setq currobj (ssadd (entlast) currobj))
(setq coords (list 
(list 3520.5625 -168.014) 
(list 3594.585 -167.764) 
(list 3594.585 -167.587) 
(list 3520.5625 -167.937)))
(apply 'command (append '("pline") coords '("c")))
(setq currobj (ssadd (entlast) currobj))
(setq coords (list 
(list 3520.5625 -167.794) 
(list 3594.585 -167.444) 
(list 3594.585 -167.267) 
(list 3520.5625 -167.717)))
(apply 'command (append '("pline") coords '("c")))
(setq currobj (ssadd (entlast) currobj))
(setq coords (list 
(list 3520.5625 -167.574) 
(list 3594.585 -167.124) 
(list 3594.585 -166.947) 
(list 3520.5625 -167.497)))
(apply 'command (append '("pline") coords '("c")))
(setq currobj (ssadd (entlast) currobj))
(setq coords (list 
(list 3520.5625 -167.354) 
(list 3594.585 -166.804) 
(list 3594.585 -166.627) 
(list 3520.5625 -167.277)))
(apply 'command (append '("pline") coords '("c")))
(setq currobj (ssadd (entlast) currobj))
(setq coords (list 
(list 3520.5625 -167.134) 
(list 3594.585 -166.484) 
(list 3594.585 -166.307) 
(list 3520.5625 -167.057)))
(apply 'command (append '("pline") coords '("c")))
(setq currobj (ssadd (entlast) currobj))
(setq coords (list 
(list 3519.4375 -167.057) 
(list 3445.415 -166.307) 
(list 3445.415 -166.484) 
(list 3519.4375 -167.134)))
(apply 'command (append '("pline") coords '("c")))
(setq currobj (ssadd (entlast) currobj))
(setq coords (list 
(list 3519.4375 -167.277) 
(list 3445.415 -166.627) 
(list 3445.415 -166.804) 
(list 3519.4375 -167.354)))
(apply 'command (append '("pline") coords '("c")))
(setq currobj (ssadd (entlast) currobj))
(setq coords (list 
(list 3519.4375 -167.497) 
(list 3445.415 -166.947) 
(list 3445.415 -167.124) 
(list 3519.4375 -167.574)))
(apply 'command (append '("pline") coords '("c")))
(setq currobj (ssadd (entlast) currobj))
(setq coords (list 
(list 3519.4375 -167.717) 
(list 3445.415 -167.267) 
(list 3445.415 -167.444) 
(list 3519.4375 -167.794)))
(apply 'command (append '("pline") coords '("c")))
(setq currobj (ssadd (entlast) currobj))
(setq coords (list 
(list 3519.4375 -167.937) 
(list 3445.415 -167.587) 
(list 3445.415 -167.764) 
(list 3519.4375 -168.014)))
(apply 'command (append '("pline") coords '("c")))
(setq currobj (ssadd (entlast) currobj))
(setq coords (list 
(list 3519.4375 -168.157) 
(list 3445.415 -167.907) 
(list 3445.415 -168.084) 
(list 3519.4375 -168.234)))
(apply 'command (append '("pline") coords '("c")))
(setq currobj (ssadd (entlast) currobj))
(setq coords (list 
(list 3519.4375 -168.377) 
(list 3445.415 -168.227) 
(list 3445.415 -168.404) 
(list 3519.4375 -168.454)))
(apply 'command (append '("pline") coords '("c")))
(setq currobj (ssadd (entlast) currobj))
(setq coords (list 
(list 3519.4375 -168.597) 
(list 3445.415 -168.547) 
(list 3445.415 -168.724) 
(list 3519.4375 -168.674)))
(apply 'command (append '("pline") coords '("c")))
(setq currobj (ssadd (entlast) currobj))
(setq coords (list 
(list 3519.4375 -168.817) 
(list 3445.415 -168.867) 
(list 3445.415 -169.044) 
(list 3519.4375 -168.894)))
(apply 'command (append '("pline") coords '("c")))
(setq currobj (ssadd (entlast) currobj))
(setq coords (list 
(list 3519.4375 -169.037) 
(list 3445.415 -169.187) 
(list 3445.415 -169.364) 
(list 3519.4375 -169.114)))
(apply 'command (append '("pline") coords '("c")))
(setq currobj (ssadd (entlast) currobj))
(setq coords (list 
(list 3519.4375 -169.257) 
(list 3445.415 -169.507) 
(list 3445.415 -169.684) 
(list 3519.4375 -169.334)))
(apply 'command (append '("pline") coords '("c")))
(setq currobj (ssadd (entlast) currobj))
(setq coords (list 
(list 3519.4375 -169.477) 
(list 3445.415 -169.827) 
(list 3445.415 -170.004) 
(list 3519.4375 -169.554)))
(apply 'command (append '("pline") coords '("c")))
(setq currobj (ssadd (entlast) currobj))
(setq coords (list 
(list 3519.4375 -169.697) 
(list 3445.415 -170.147) 
(list 3445.415 -170.324) 
(list 3519.4375 -169.774)))
(apply 'command (append '("pline") coords '("c")))
(setq currobj (ssadd (entlast) currobj))
(setq coords (list 
(list 3519.4375 -169.917) 
(list 3445.415 -170.467) 
(list 3445.415 -170.644) 
(list 3519.4375 -169.994)))
(apply 'command (append '("pline") coords '("c")))
(setq currobj (ssadd (entlast) currobj))
(setq coords (list 
(list 3519.4375 -170.137) 
(list 3445.415 -170.787) 
(list 3445.415 -170.964) 
(list 3519.4375 -170.214)))
(apply 'command (append '("pline") coords '("c")))
(setq currobj (ssadd (entlast) currobj))
(command "_layer" "set" "nitride" "")
(command "_layer" "set" "text" "")
(command "_circle" "3519.0625,-181.357" "0.075")
(command "_circle" "3519.0625,-181.057" "0.075")
(command "_circle" "3519.0625,-180.757" "0.075")
(command "_circle" "3519.0625,-180.457" "0.075")
(command "_circle" "3519.0625,-180.157" "0.075")
(command "_circle" "3518.7625,-181.357" "0.075")
(command "_circle" "3518.7625,-181.057" "0.075")
(command "_circle" "3518.7625,-180.757" "0.075")
(command "_circle" "3518.7625,-180.457" "0.075")
(command "_circle" "3518.7625,-180.157" "0.075")
(command "_circle" "3518.4625,-181.357" "0.075")
(command "_circle" "3518.4625,-181.057" "0.075")
(command "_circle" "3518.4625,-180.757" "0.075")
(command "_circle" "3518.4625,-180.457" "0.075")
(command "_circle" "3518.4625,-180.157" "0.075")
(command "_circle" "3518.1625,-181.357" "0.075")
(command "_circle" "3518.1625,-181.057" "0.075")
(command "_circle" "3518.1625,-180.757" "0.075")
(command "_circle" "3518.1625,-180.457" "0.075")
(command "_circle" "3518.1625,-180.157" "0.075")
(command "_circle" "3517.8625,-181.357" "0.075")
(command "_circle" "3517.8625,-181.057" "0.075")
(command "_circle" "3517.8625,-180.757" "0.075")
(command "_circle" "3517.8625,-180.457" "0.075")
(command "_circle" "3517.8625,-180.157" "0.075")
(command "_layer" "set" "nitride" "")
(setq coords (list 
(list 3520.2625 -155.914) 
(list 3520.2625 -40.2693) 
(list 3519.7375 -40.2693) 
(list 3519.7375 -155.914)))
(apply 'command (append '("pline") coords '("c")))
(setq currobj (ssadd (entlast) currobj))
(command "_layer" "set" "prebias" "")
(command "_rectangle" "3519.7375,-155.914" "3520.2625,-40.2693")
(setq currobj (ssadd (entlast) currobj))
(command "_layer" "set" "nitride" "")
(setq coords (list 
(list 3520.2625 -40.2693) 
(list 3520.5625 -30.2693) 
(list 3520.5625 -30.2693) 
(list 3520.5625 -29.2693) 
(list 3594.585 -30.0193) 
(list 3594.585 -25.0763) 
(list 3520.5625 -25.8263) 
(list 3520.5625 -24.8263) 
(list 3520.5625 -24.8263) 
(list 3520.2625 -14.8263) 
(list 3519.7375 -14.8263) 
(list 3519.4375 -24.8263) 
(list 3519.4375 -24.8263) 
(list 3519.4375 -25.8263) 
(list 3445.415 -25.0763) 
(list 3445.415 -30.0193) 
(list 3519.4375 -29.2693) 
(list 3519.4375 -30.2693) 
(list 3519.4375 -30.2693) 
(list 3519.7375 -40.2693)))
(apply 'command (append '("pline") coords '("c")))
(setq currobj (ssadd (entlast) currobj))
(command "_layer" "set" "prebias" "")
(setq coords (list 
(list 3519.4375 -40.2693) 
(list 3519.4375 -29.2693) 
(list 3445.415 -30.0193) 
(list 3445.415 -25.0763) 
(list 3519.4375 -25.8263) 
(list 3519.4375 -14.8263) 
(list 3520.5625 -14.8263) 
(list 3520.5625 -25.8263) 
(list 3594.585 -25.0763) 
(list 3594.585 -30.0193) 
(list 3520.5625 -29.2693) 
(list 3520.5625 -40.2693)))
(apply 'command (append '("pline") coords '("c")))
(setq currobj (ssadd (entlast) currobj))
(command "_layer" "set" "nitride" "")
(command "_layer" "set" "fda1" "")
(setq coords (list 
(list 3520.5625 -29.1263) 
(list 3594.585 -29.8763) 
(list 3594.585 -29.6993) 
(list 3520.5625 -29.0493)))
(apply 'command (append '("pline") coords '("c")))
(setq currobj (ssadd (entlast) currobj))
(setq coords (list 
(list 3520.5625 -28.9063) 
(list 3594.585 -29.5563) 
(list 3594.585 -29.3793) 
(list 3520.5625 -28.8293)))
(apply 'command (append '("pline") coords '("c")))
(setq currobj (ssadd (entlast) currobj))
(setq coords (list 
(list 3520.5625 -28.6863) 
(list 3594.585 -29.2363) 
(list 3594.585 -29.0593) 
(list 3520.5625 -28.6093)))
(apply 'command (append '("pline") coords '("c")))
(setq currobj (ssadd (entlast) currobj))
(setq coords (list 
(list 3520.5625 -28.4663) 
(list 3594.585 -28.9163) 
(list 3594.585 -28.7393) 
(list 3520.5625 -28.3893)))
(apply 'command (append '("pline") coords '("c")))
(setq currobj (ssadd (entlast) currobj))
(setq coords (list 
(list 3520.5625 -28.2463) 
(list 3594.585 -28.5963) 
(list 3594.585 -28.4193) 
(list 3520.5625 -28.1693)))
(apply 'command (append '("pline") coords '("c")))
(setq currobj (ssadd (entlast) currobj))
(setq coords (list 
(list 3520.5625 -28.0263) 
(list 3594.585 -28.2763) 
(list 3594.585 -28.0993) 
(list 3520.5625 -27.9493)))
(apply 'command (append '("pline") coords '("c")))
(setq currobj (ssadd (entlast) currobj))
(setq coords (list 
(list 3520.5625 -27.8063) 
(list 3594.585 -27.9563) 
(list 3594.585 -27.7793) 
(list 3520.5625 -27.7293)))
(apply 'command (append '("pline") coords '("c")))
(setq currobj (ssadd (entlast) currobj))
(setq coords (list 
(list 3520.5625 -27.5863) 
(list 3594.585 -27.6363) 
(list 3594.585 -27.4593) 
(list 3520.5625 -27.5093)))
(apply 'command (append '("pline") coords '("c")))
(setq currobj (ssadd (entlast) currobj))
(setq coords (list 
(list 3520.5625 -27.3663) 
(list 3594.585 -27.3163) 
(list 3594.585 -27.1393) 
(list 3520.5625 -27.2893)))
(apply 'command (append '("pline") coords '("c")))
(setq currobj (ssadd (entlast) currobj))
(setq coords (list 
(list 3520.5625 -27.1463) 
(list 3594.585 -26.9963) 
(list 3594.585 -26.8193) 
(list 3520.5625 -27.0693)))
(apply 'command (append '("pline") coords '("c")))
(setq currobj (ssadd (entlast) currobj))
(setq coords (list 
(list 3520.5625 -26.9263) 
(list 3594.585 -26.6763) 
(list 3594.585 -26.4993) 
(list 3520.5625 -26.8493)))
(apply 'command (append '("pline") coords '("c")))
(setq currobj (ssadd (entlast) currobj))
(setq coords (list 
(list 3520.5625 -26.7063) 
(list 3594.585 -26.3563) 
(list 3594.585 -26.1793) 
(list 3520.5625 -26.6293)))
(apply 'command (append '("pline") coords '("c")))
(setq currobj (ssadd (entlast) currobj))
(setq coords (list 
(list 3520.5625 -26.4863) 
(list 3594.585 -26.0363) 
(list 3594.585 -25.8593) 
(list 3520.5625 -26.4093)))
(apply 'command (append '("pline") coords '("c")))
(setq currobj (ssadd (entlast) currobj))
(setq coords (list 
(list 3520.5625 -26.2663) 
(list 3594.585 -25.7163) 
(list 3594.585 -25.5393) 
(list 3520.5625 -26.1893)))
(apply 'command (append '("pline") coords '("c")))
(setq currobj (ssadd (entlast) currobj))
(setq coords (list 
(list 3520.5625 -26.0463) 
(list 3594.585 -25.3963) 
(list 3594.585 -25.2193) 
(list 3520.5625 -25.9693)))
(apply 'command (append '("pline") coords '("c")))
(setq currobj (ssadd (entlast) currobj))
(setq coords (list 
(list 3519.4375 -25.9693) 
(list 3445.415 -25.2193) 
(list 3445.415 -25.3963) 
(list 3519.4375 -26.0463)))
(apply 'command (append '("pline") coords '("c")))
(setq currobj (ssadd (entlast) currobj))
(setq coords (list 
(list 3519.4375 -26.1893) 
(list 3445.415 -25.5393) 
(list 3445.415 -25.7163) 
(list 3519.4375 -26.2663)))
(apply 'command (append '("pline") coords '("c")))
(setq currobj (ssadd (entlast) currobj))
(setq coords (list 
(list 3519.4375 -26.4093) 
(list 3445.415 -25.8593) 
(list 3445.415 -26.0363) 
(list 3519.4375 -26.4863)))
(apply 'command (append '("pline") coords '("c")))
(setq currobj (ssadd (entlast) currobj))
(setq coords (list 
(list 3519.4375 -26.6293) 
(list 3445.415 -26.1793) 
(list 3445.415 -26.3563) 
(list 3519.4375 -26.7063)))
(apply 'command (append '("pline") coords '("c")))
(setq currobj (ssadd (entlast) currobj))
(setq coords (list 
(list 3519.4375 -26.8493) 
(list 3445.415 -26.4993) 
(list 3445.415 -26.6763) 
(list 3519.4375 -26.9263)))
(apply 'command (append '("pline") coords '("c")))
(setq currobj (ssadd (entlast) currobj))
(setq coords (list 
(list 3519.4375 -27.0693) 
(list 3445.415 -26.8193) 
(list 3445.415 -26.9963) 
(list 3519.4375 -27.1463)))
(apply 'command (append '("pline") coords '("c")))
(setq currobj (ssadd (entlast) currobj))
(setq coords (list 
(list 3519.4375 -27.2893) 
(list 3445.415 -27.1393) 
(list 3445.415 -27.3163) 
(list 3519.4375 -27.3663)))
(apply 'command (append '("pline") coords '("c")))
(setq currobj (ssadd (entlast) currobj))
(setq coords (list 
(list 3519.4375 -27.5093) 
(list 3445.415 -27.4593) 
(list 3445.415 -27.6363) 
(list 3519.4375 -27.5863)))
(apply 'command (append '("pline") coords '("c")))
(setq currobj (ssadd (entlast) currobj))
(setq coords (list 
(list 3519.4375 -27.7293) 
(list 3445.415 -27.7793) 
(list 3445.415 -27.9563) 
(list 3519.4375 -27.8063)))
(apply 'command (append '("pline") coords '("c")))
(setq currobj (ssadd (entlast) currobj))
(setq coords (list 
(list 3519.4375 -27.9493) 
(list 3445.415 -28.0993) 
(list 3445.415 -28.2763) 
(list 3519.4375 -28.0263)))
(apply 'command (append '("pline") coords '("c")))
(setq currobj (ssadd (entlast) currobj))
(setq coords (list 
(list 3519.4375 -28.1693) 
(list 3445.415 -28.4193) 
(list 3445.415 -28.5963) 
(list 3519.4375 -28.2463)))
(apply 'command (append '("pline") coords '("c")))
(setq currobj (ssadd (entlast) currobj))
(setq coords (list 
(list 3519.4375 -28.3893) 
(list 3445.415 -28.7393) 
(list 3445.415 -28.9163) 
(list 3519.4375 -28.4663)))
(apply 'command (append '("pline") coords '("c")))
(setq currobj (ssadd (entlast) currobj))
(setq coords (list 
(list 3519.4375 -28.6093) 
(list 3445.415 -29.0593) 
(list 3445.415 -29.2363) 
(list 3519.4375 -28.6863)))
(apply 'command (append '("pline") coords '("c")))
(setq currobj (ssadd (entlast) currobj))
(setq coords (list 
(list 3519.4375 -28.8293) 
(list 3445.415 -29.3793) 
(list 3445.415 -29.5563) 
(list 3519.4375 -28.9063)))
(apply 'command (append '("pline") coords '("c")))
(setq currobj (ssadd (entlast) currobj))
(setq coords (list 
(list 3519.4375 -29.0493) 
(list 3445.415 -29.6993) 
(list 3445.415 -29.8763) 
(list 3519.4375 -29.1263)))
(apply 'command (append '("pline") coords '("c")))
(setq currobj (ssadd (entlast) currobj))
(command "_layer" "set" "nitride" "")
(command "_layer" "set" "text" "")
(command "_circle" "3519.0625,-40.2693" "0.075")
(command "_circle" "3519.0625,-39.9693" "0.075")
(command "_circle" "3519.0625,-39.6693" "0.075")
(command "_circle" "3519.0625,-39.3693" "0.075")
(command "_circle" "3519.0625,-39.0693" "0.075")
(command "_circle" "3518.7625,-40.2693" "0.075")
(command "_circle" "3518.7625,-39.9693" "0.075")
(command "_circle" "3518.7625,-39.6693" "0.075")
(command "_circle" "3518.7625,-39.3693" "0.075")
(command "_circle" "3518.7625,-39.0693" "0.075")
(command "_circle" "3518.4625,-40.2693" "0.075")
(command "_circle" "3518.4625,-39.9693" "0.075")
(command "_circle" "3518.4625,-39.6693" "0.075")
(command "_circle" "3518.4625,-39.3693" "0.075")
(command "_circle" "3518.4625,-39.0693" "0.075")
(command "_circle" "3518.1625,-40.2693" "0.075")
(command "_circle" "3518.1625,-39.9693" "0.075")
(command "_circle" "3518.1625,-39.6693" "0.075")
(command "_circle" "3518.1625,-39.3693" "0.075")
(command "_circle" "3518.1625,-39.0693" "0.075")
(command "_circle" "3517.8625,-40.2693" "0.075")
(command "_circle" "3517.8625,-39.9693" "0.075")
(command "_circle" "3517.8625,-39.6693" "0.075")
(command "_circle" "3517.8625,-39.3693" "0.075")
(command "_circle" "3517.8625,-39.0693" "0.075")
(command "_layer" "set" "nitride" "")
(setq coords (list 
(list 3520.2625 -14.8263) 
(list 3520.2625 100.8184) 
(list 3519.7375 100.8184) 
(list 3519.7375 -14.8263)))
(apply 'command (append '("pline") coords '("c")))
(setq currobj (ssadd (entlast) currobj))
(command "_layer" "set" "prebias" "")
(command "_rectangle" "3519.7375,-14.8263" "3520.2625,100.8184")
(setq currobj (ssadd (entlast) currobj))
(command "_layer" "set" "nitride" "")
(setq coords (list 
(list 3520.2625 100.8184) 
(list 3520.5625 110.8184) 
(list 3520.5625 110.8184) 
(list 3520.5625 111.8184) 
(list 3594.585 111.0684) 
(list 3594.585 116.0114) 
(list 3520.5625 115.2614) 
(list 3520.5625 116.2614) 
(list 3520.5625 116.2614) 
(list 3520.2625 126.2614) 
(list 3519.7375 126.2614) 
(list 3519.4375 116.2614) 
(list 3519.4375 116.2614) 
(list 3519.4375 115.2614) 
(list 3445.415 116.0114) 
(list 3445.415 111.0684) 
(list 3519.4375 111.8184) 
(list 3519.4375 110.8184) 
(list 3519.4375 110.8184) 
(list 3519.7375 100.8184)))
(apply 'command (append '("pline") coords '("c")))
(setq currobj (ssadd (entlast) currobj))
(command "_layer" "set" "prebias" "")
(setq coords (list 
(list 3519.4375 100.8184) 
(list 3519.4375 111.8184) 
(list 3445.415 111.0684) 
(list 3445.415 116.0114) 
(list 3519.4375 115.2614) 
(list 3519.4375 126.2614) 
(list 3520.5625 126.2614) 
(list 3520.5625 115.2614) 
(list 3594.585 116.0114) 
(list 3594.585 111.0684) 
(list 3520.5625 111.8184) 
(list 3520.5625 100.8184)))
(apply 'command (append '("pline") coords '("c")))
(setq currobj (ssadd (entlast) currobj))
(command "_layer" "set" "nitride" "")
(command "_layer" "set" "fda1" "")
(setq coords (list 
(list 3520.5625 111.9614) 
(list 3594.585 111.2114) 
(list 3594.585 111.3884) 
(list 3520.5625 112.0384)))
(apply 'command (append '("pline") coords '("c")))
(setq currobj (ssadd (entlast) currobj))
(setq coords (list 
(list 3520.5625 112.1814) 
(list 3594.585 111.5314) 
(list 3594.585 111.7084) 
(list 3520.5625 112.2584)))
(apply 'command (append '("pline") coords '("c")))
(setq currobj (ssadd (entlast) currobj))
(setq coords (list 
(list 3520.5625 112.4014) 
(list 3594.585 111.8514) 
(list 3594.585 112.0284) 
(list 3520.5625 112.4784)))
(apply 'command (append '("pline") coords '("c")))
(setq currobj (ssadd (entlast) currobj))
(setq coords (list 
(list 3520.5625 112.6214) 
(list 3594.585 112.1714) 
(list 3594.585 112.3484) 
(list 3520.5625 112.6984)))
(apply 'command (append '("pline") coords '("c")))
(setq currobj (ssadd (entlast) currobj))
(setq coords (list 
(list 3520.5625 112.8414) 
(list 3594.585 112.4914) 
(list 3594.585 112.6684) 
(list 3520.5625 112.9184)))
(apply 'command (append '("pline") coords '("c")))
(setq currobj (ssadd (entlast) currobj))
(setq coords (list 
(list 3520.5625 113.0614) 
(list 3594.585 112.8114) 
(list 3594.585 112.9884) 
(list 3520.5625 113.1384)))
(apply 'command (append '("pline") coords '("c")))
(setq currobj (ssadd (entlast) currobj))
(setq coords (list 
(list 3520.5625 113.2814) 
(list 3594.585 113.1314) 
(list 3594.585 113.3084) 
(list 3520.5625 113.3584)))
(apply 'command (append '("pline") coords '("c")))
(setq currobj (ssadd (entlast) currobj))
(setq coords (list 
(list 3520.5625 113.5014) 
(list 3594.585 113.4514) 
(list 3594.585 113.6284) 
(list 3520.5625 113.5784)))
(apply 'command (append '("pline") coords '("c")))
(setq currobj (ssadd (entlast) currobj))
(setq coords (list 
(list 3520.5625 113.7214) 
(list 3594.585 113.7714) 
(list 3594.585 113.9484) 
(list 3520.5625 113.7984)))
(apply 'command (append '("pline") coords '("c")))
(setq currobj (ssadd (entlast) currobj))
(setq coords (list 
(list 3520.5625 113.9414) 
(list 3594.585 114.0914) 
(list 3594.585 114.2684) 
(list 3520.5625 114.0184)))
(apply 'command (append '("pline") coords '("c")))
(setq currobj (ssadd (entlast) currobj))
(setq coords (list 
(list 3520.5625 114.1614) 
(list 3594.585 114.4114) 
(list 3594.585 114.5884) 
(list 3520.5625 114.2384)))
(apply 'command (append '("pline") coords '("c")))
(setq currobj (ssadd (entlast) currobj))
(setq coords (list 
(list 3520.5625 114.3814) 
(list 3594.585 114.7314) 
(list 3594.585 114.9084) 
(list 3520.5625 114.4584)))
(apply 'command (append '("pline") coords '("c")))
(setq currobj (ssadd (entlast) currobj))
(setq coords (list 
(list 3520.5625 114.6014) 
(list 3594.585 115.0514) 
(list 3594.585 115.2284) 
(list 3520.5625 114.6784)))
(apply 'command (append '("pline") coords '("c")))
(setq currobj (ssadd (entlast) currobj))
(setq coords (list 
(list 3520.5625 114.8214) 
(list 3594.585 115.3714) 
(list 3594.585 115.5484) 
(list 3520.5625 114.8984)))
(apply 'command (append '("pline") coords '("c")))
(setq currobj (ssadd (entlast) currobj))
(setq coords (list 
(list 3520.5625 115.0414) 
(list 3594.585 115.6914) 
(list 3594.585 115.8684) 
(list 3520.5625 115.1184)))
(apply 'command (append '("pline") coords '("c")))
(setq currobj (ssadd (entlast) currobj))
(setq coords (list 
(list 3519.4375 115.1184) 
(list 3445.415 115.8684) 
(list 3445.415 115.6914) 
(list 3519.4375 115.0414)))
(apply 'command (append '("pline") coords '("c")))
(setq currobj (ssadd (entlast) currobj))
(setq coords (list 
(list 3519.4375 114.8984) 
(list 3445.415 115.5484) 
(list 3445.415 115.3714) 
(list 3519.4375 114.8214)))
(apply 'command (append '("pline") coords '("c")))
(setq currobj (ssadd (entlast) currobj))
(setq coords (list 
(list 3519.4375 114.6784) 
(list 3445.415 115.2284) 
(list 3445.415 115.0514) 
(list 3519.4375 114.6014)))
(apply 'command (append '("pline") coords '("c")))
(setq currobj (ssadd (entlast) currobj))
(setq coords (list 
(list 3519.4375 114.4584) 
(list 3445.415 114.9084) 
(list 3445.415 114.7314) 
(list 3519.4375 114.3814)))
(apply 'command (append '("pline") coords '("c")))
(setq currobj (ssadd (entlast) currobj))
(setq coords (list 
(list 3519.4375 114.2384) 
(list 3445.415 114.5884) 
(list 3445.415 114.4114) 
(list 3519.4375 114.1614)))
(apply 'command (append '("pline") coords '("c")))
(setq currobj (ssadd (entlast) currobj))
(setq coords (list 
(list 3519.4375 114.0184) 
(list 3445.415 114.2684) 
(list 3445.415 114.0914) 
(list 3519.4375 113.9414)))
(apply 'command (append '("pline") coords '("c")))
(setq currobj (ssadd (entlast) currobj))
(setq coords (list 
(list 3519.4375 113.7984) 
(list 3445.415 113.9484) 
(list 3445.415 113.7714) 
(list 3519.4375 113.7214)))
(apply 'command (append '("pline") coords '("c")))
(setq currobj (ssadd (entlast) currobj))
(setq coords (list 
(list 3519.4375 113.5784) 
(list 3445.415 113.6284) 
(list 3445.415 113.4514) 
(list 3519.4375 113.5014)))
(apply 'command (append '("pline") coords '("c")))
(setq currobj (ssadd (entlast) currobj))
(setq coords (list 
(list 3519.4375 113.3584) 
(list 3445.415 113.3084) 
(list 3445.415 113.1314) 
(list 3519.4375 113.2814)))
(apply 'command (append '("pline") coords '("c")))
(setq currobj (ssadd (entlast) currobj))
(setq coords (list 
(list 3519.4375 113.1384) 
(list 3445.415 112.9884) 
(list 3445.415 112.8114) 
(list 3519.4375 113.0614)))
(apply 'command (append '("pline") coords '("c")))
(setq currobj (ssadd (entlast) currobj))
(setq coords (list 
(list 3519.4375 112.9184) 
(list 3445.415 112.6684) 
(list 3445.415 112.4914) 
(list 3519.4375 112.8414)))
(apply 'command (append '("pline") coords '("c")))
(setq currobj (ssadd (entlast) currobj))
(setq coords (list 
(list 3519.4375 112.6984) 
(list 3445.415 112.3484) 
(list 3445.415 112.1714) 
(list 3519.4375 112.6214)))
(apply 'command (append '("pline") coords '("c")))
(setq currobj (ssadd (entlast) currobj))
(setq coords (list 
(list 3519.4375 112.4784) 
(list 3445.415 112.0284) 
(list 3445.415 111.8514) 
(list 3519.4375 112.4014)))
(apply 'command (append '("pline") coords '("c")))
(setq currobj (ssadd (entlast) currobj))
(setq coords (list 
(list 3519.4375 112.2584) 
(list 3445.415 111.7084) 
(list 3445.415 111.5314) 
(list 3519.4375 112.1814)))
(apply 'command (append '("pline") coords '("c")))
(setq currobj (ssadd (entlast) currobj))
(setq coords (list 
(list 3519.4375 112.0384) 
(list 3445.415 111.3884) 
(list 3445.415 111.2114) 
(list 3519.4375 111.9614)))
(apply 'command (append '("pline") coords '("c")))
(setq currobj (ssadd (entlast) currobj))
(command "_layer" "set" "nitride" "")
(command "_layer" "set" "text" "")
(command "_circle" "3519.0625,100.8184" "0.075")
(command "_circle" "3519.0625,101.1184" "0.075")
(command "_circle" "3519.0625,101.4184" "0.075")
(command "_circle" "3519.0625,101.7184" "0.075")
(command "_circle" "3519.0625,102.0184" "0.075")
(command "_circle" "3518.7625,100.8184" "0.075")
(command "_circle" "3518.7625,101.1184" "0.075")
(command "_circle" "3518.7625,101.4184" "0.075")
(command "_circle" "3518.7625,101.7184" "0.075")
(command "_circle" "3518.7625,102.0184" "0.075")
(command "_circle" "3518.4625,100.8184" "0.075")
(command "_circle" "3518.4625,101.1184" "0.075")
(command "_circle" "3518.4625,101.4184" "0.075")
(command "_circle" "3518.4625,101.7184" "0.075")
(command "_circle" "3518.4625,102.0184" "0.075")
(command "_circle" "3518.1625,100.8184" "0.075")
(command "_circle" "3518.1625,101.1184" "0.075")
(command "_circle" "3518.1625,101.4184" "0.075")
(command "_circle" "3518.1625,101.7184" "0.075")
(command "_circle" "3518.1625,102.0184" "0.075")
(command "_circle" "3517.8625,100.8184" "0.075")
(command "_circle" "3517.8625,101.1184" "0.075")
(command "_circle" "3517.8625,101.4184" "0.075")
(command "_circle" "3517.8625,101.7184" "0.075")
(command "_circle" "3517.8625,102.0184" "0.075")
(command "_layer" "set" "nitride" "")
(setq coords (list 
(list 3520.2625 126.2614) 
(list 3520.2625 241.9061) 
(list 3519.7375 241.9061) 
(list 3519.7375 126.2614)))
(apply 'command (append '("pline") coords '("c")))
(setq currobj (ssadd (entlast) currobj))
(command "_layer" "set" "prebias" "")
(command "_rectangle" "3519.7375,126.2614" "3520.2625,241.9061")
(setq currobj (ssadd (entlast) currobj))
(command "_layer" "set" "nitride" "")
(setq coords (list 
(list 3520.2625 241.9061) 
(list 3520.5625 251.9061) 
(list 3520.5625 251.9061) 
(list 3520.5625 252.9061) 
(list 3594.585 252.1561) 
(list 3594.585 257.0991) 
(list 3520.5625 256.3491) 
(list 3520.5625 257.3491) 
(list 3520.5625 257.3491) 
(list 3520.2625 267.3491) 
(list 3519.7375 267.3491) 
(list 3519.4375 257.3491) 
(list 3519.4375 257.3491) 
(list 3519.4375 256.3491) 
(list 3445.415 257.0991) 
(list 3445.415 252.1561) 
(list 3519.4375 252.9061) 
(list 3519.4375 251.9061) 
(list 3519.4375 251.9061) 
(list 3519.7375 241.9061)))
(apply 'command (append '("pline") coords '("c")))
(setq currobj (ssadd (entlast) currobj))
(command "_layer" "set" "prebias" "")
(setq coords (list 
(list 3519.4375 241.9061) 
(list 3519.4375 252.9061) 
(list 3445.415 252.1561) 
(list 3445.415 257.0991) 
(list 3519.4375 256.3491) 
(list 3519.4375 267.3491) 
(list 3520.5625 267.3491) 
(list 3520.5625 256.3491) 
(list 3594.585 257.0991) 
(list 3594.585 252.1561) 
(list 3520.5625 252.9061) 
(list 3520.5625 241.9061)))
(apply 'command (append '("pline") coords '("c")))
(setq currobj (ssadd (entlast) currobj))
(command "_layer" "set" "nitride" "")
(command "_layer" "set" "fda1" "")
(setq coords (list 
(list 3520.5625 253.0491) 
(list 3594.585 252.2991) 
(list 3594.585 252.4761) 
(list 3520.5625 253.1261)))
(apply 'command (append '("pline") coords '("c")))
(setq currobj (ssadd (entlast) currobj))
(setq coords (list 
(list 3520.5625 253.2691) 
(list 3594.585 252.6191) 
(list 3594.585 252.7961) 
(list 3520.5625 253.3461)))
(apply 'command (append '("pline") coords '("c")))
(setq currobj (ssadd (entlast) currobj))
(setq coords (list 
(list 3520.5625 253.4891) 
(list 3594.585 252.9391) 
(list 3594.585 253.1161) 
(list 3520.5625 253.5661)))
(apply 'command (append '("pline") coords '("c")))
(setq currobj (ssadd (entlast) currobj))
(setq coords (list 
(list 3520.5625 253.7091) 
(list 3594.585 253.2591) 
(list 3594.585 253.4361) 
(list 3520.5625 253.7861)))
(apply 'command (append '("pline") coords '("c")))
(setq currobj (ssadd (entlast) currobj))
(setq coords (list 
(list 3520.5625 253.9291) 
(list 3594.585 253.5791) 
(list 3594.585 253.7561) 
(list 3520.5625 254.0061)))
(apply 'command (append '("pline") coords '("c")))
(setq currobj (ssadd (entlast) currobj))
(setq coords (list 
(list 3520.5625 254.1491) 
(list 3594.585 253.8991) 
(list 3594.585 254.0761) 
(list 3520.5625 254.2261)))
(apply 'command (append '("pline") coords '("c")))
(setq currobj (ssadd (entlast) currobj))
(setq coords (list 
(list 3520.5625 254.3691) 
(list 3594.585 254.2191) 
(list 3594.585 254.3961) 
(list 3520.5625 254.4461)))
(apply 'command (append '("pline") coords '("c")))
(setq currobj (ssadd (entlast) currobj))
(setq coords (list 
(list 3520.5625 254.5891) 
(list 3594.585 254.5391) 
(list 3594.585 254.7161) 
(list 3520.5625 254.6661)))
(apply 'command (append '("pline") coords '("c")))
(setq currobj (ssadd (entlast) currobj))
(setq coords (list 
(list 3520.5625 254.8091) 
(list 3594.585 254.8591) 
(list 3594.585 255.0361) 
(list 3520.5625 254.8861)))
(apply 'command (append '("pline") coords '("c")))
(setq currobj (ssadd (entlast) currobj))
(setq coords (list 
(list 3520.5625 255.0291) 
(list 3594.585 255.1791) 
(list 3594.585 255.3561) 
(list 3520.5625 255.1061)))
(apply 'command (append '("pline") coords '("c")))
(setq currobj (ssadd (entlast) currobj))
(setq coords (list 
(list 3520.5625 255.2491) 
(list 3594.585 255.4991) 
(list 3594.585 255.6761) 
(list 3520.5625 255.3261)))
(apply 'command (append '("pline") coords '("c")))
(setq currobj (ssadd (entlast) currobj))
(setq coords (list 
(list 3520.5625 255.4691) 
(list 3594.585 255.8191) 
(list 3594.585 255.9961) 
(list 3520.5625 255.5461)))
(apply 'command (append '("pline") coords '("c")))
(setq currobj (ssadd (entlast) currobj))
(setq coords (list 
(list 3520.5625 255.6891) 
(list 3594.585 256.1391) 
(list 3594.585 256.3161) 
(list 3520.5625 255.7661)))
(apply 'command (append '("pline") coords '("c")))
(setq currobj (ssadd (entlast) currobj))
(setq coords (list 
(list 3520.5625 255.9091) 
(list 3594.585 256.4591) 
(list 3594.585 256.6361) 
(list 3520.5625 255.9861)))
(apply 'command (append '("pline") coords '("c")))
(setq currobj (ssadd (entlast) currobj))
(setq coords (list 
(list 3520.5625 256.1291) 
(list 3594.585 256.7791) 
(list 3594.585 256.9561) 
(list 3520.5625 256.2061)))
(apply 'command (append '("pline") coords '("c")))
(setq currobj (ssadd (entlast) currobj))
(setq coords (list 
(list 3519.4375 256.2061) 
(list 3445.415 256.9561) 
(list 3445.415 256.7791) 
(list 3519.4375 256.1291)))
(apply 'command (append '("pline") coords '("c")))
(setq currobj (ssadd (entlast) currobj))
(setq coords (list 
(list 3519.4375 255.9861) 
(list 3445.415 256.6361) 
(list 3445.415 256.4591) 
(list 3519.4375 255.9091)))
(apply 'command (append '("pline") coords '("c")))
(setq currobj (ssadd (entlast) currobj))
(setq coords (list 
(list 3519.4375 255.7661) 
(list 3445.415 256.3161) 
(list 3445.415 256.1391) 
(list 3519.4375 255.6891)))
(apply 'command (append '("pline") coords '("c")))
(setq currobj (ssadd (entlast) currobj))
(setq coords (list 
(list 3519.4375 255.5461) 
(list 3445.415 255.9961) 
(list 3445.415 255.8191) 
(list 3519.4375 255.4691)))
(apply 'command (append '("pline") coords '("c")))
(setq currobj (ssadd (entlast) currobj))
(setq coords (list 
(list 3519.4375 255.3261) 
(list 3445.415 255.6761) 
(list 3445.415 255.4991) 
(list 3519.4375 255.2491)))
(apply 'command (append '("pline") coords '("c")))
(setq currobj (ssadd (entlast) currobj))
(setq coords (list 
(list 3519.4375 255.1061) 
(list 3445.415 255.3561) 
(list 3445.415 255.1791) 
(list 3519.4375 255.0291)))
(apply 'command (append '("pline") coords '("c")))
(setq currobj (ssadd (entlast) currobj))
(setq coords (list 
(list 3519.4375 254.8861) 
(list 3445.415 255.0361) 
(list 3445.415 254.8591) 
(list 3519.4375 254.8091)))
(apply 'command (append '("pline") coords '("c")))
(setq currobj (ssadd (entlast) currobj))
(setq coords (list 
(list 3519.4375 254.6661) 
(list 3445.415 254.7161) 
(list 3445.415 254.5391) 
(list 3519.4375 254.5891)))
(apply 'command (append '("pline") coords '("c")))
(setq currobj (ssadd (entlast) currobj))
(setq coords (list 
(list 3519.4375 254.4461) 
(list 3445.415 254.3961) 
(list 3445.415 254.2191) 
(list 3519.4375 254.3691)))
(apply 'command (append '("pline") coords '("c")))
(setq currobj (ssadd (entlast) currobj))
(setq coords (list 
(list 3519.4375 254.2261) 
(list 3445.415 254.0761) 
(list 3445.415 253.8991) 
(list 3519.4375 254.1491)))
(apply 'command (append '("pline") coords '("c")))
(setq currobj (ssadd (entlast) currobj))
(setq coords (list 
(list 3519.4375 254.0061) 
(list 3445.415 253.7561) 
(list 3445.415 253.5791) 
(list 3519.4375 253.9291)))
(apply 'command (append '("pline") coords '("c")))
(setq currobj (ssadd (entlast) currobj))
(setq coords (list 
(list 3519.4375 253.7861) 
(list 3445.415 253.4361) 
(list 3445.415 253.2591) 
(list 3519.4375 253.7091)))
(apply 'command (append '("pline") coords '("c")))
(setq currobj (ssadd (entlast) currobj))
(setq coords (list 
(list 3519.4375 253.5661) 
(list 3445.415 253.1161) 
(list 3445.415 252.9391) 
(list 3519.4375 253.4891)))
(apply 'command (append '("pline") coords '("c")))
(setq currobj (ssadd (entlast) currobj))
(setq coords (list 
(list 3519.4375 253.3461) 
(list 3445.415 252.7961) 
(list 3445.415 252.6191) 
(list 3519.4375 253.2691)))
(apply 'command (append '("pline") coords '("c")))
(setq currobj (ssadd (entlast) currobj))
(setq coords (list 
(list 3519.4375 253.1261) 
(list 3445.415 252.4761) 
(list 3445.415 252.2991) 
(list 3519.4375 253.0491)))
(apply 'command (append '("pline") coords '("c")))
(setq currobj (ssadd (entlast) currobj))
(command "_layer" "set" "nitride" "")
(command "_layer" "set" "text" "")
(command "_circle" "3519.0625,241.9061" "0.075")
(command "_circle" "3519.0625,242.2061" "0.075")
(command "_circle" "3519.0625,242.5061" "0.075")
(command "_circle" "3519.0625,242.8061" "0.075")
(command "_circle" "3519.0625,243.1061" "0.075")
(command "_circle" "3518.7625,241.9061" "0.075")
(command "_circle" "3518.7625,242.2061" "0.075")
(command "_circle" "3518.7625,242.5061" "0.075")
(command "_circle" "3518.7625,242.8061" "0.075")
(command "_circle" "3518.7625,243.1061" "0.075")
(command "_circle" "3518.4625,241.9061" "0.075")
(command "_circle" "3518.4625,242.2061" "0.075")
(command "_circle" "3518.4625,242.5061" "0.075")
(command "_circle" "3518.4625,242.8061" "0.075")
(command "_circle" "3518.4625,243.1061" "0.075")
(command "_circle" "3518.1625,241.9061" "0.075")
(command "_circle" "3518.1625,242.2061" "0.075")
(command "_circle" "3518.1625,242.5061" "0.075")
(command "_circle" "3518.1625,242.8061" "0.075")
(command "_circle" "3518.1625,243.1061" "0.075")
(command "_circle" "3517.8625,241.9061" "0.075")
(command "_circle" "3517.8625,242.2061" "0.075")
(command "_circle" "3517.8625,242.5061" "0.075")
(command "_circle" "3517.8625,242.8061" "0.075")
(command "_circle" "3517.8625,243.1061" "0.075")
(command "_layer" "set" "nitride" "")
(setq coords (list 
(list 3520.2625 267.3491) 
(list 3520.2625 382.9939) 
(list 3519.7375 382.9939) 
(list 3519.7375 267.3491)))
(apply 'command (append '("pline") coords '("c")))
(setq currobj (ssadd (entlast) currobj))
(command "_layer" "set" "prebias" "")
(command "_rectangle" "3519.7375,267.3491" "3520.2625,382.9939")
(setq currobj (ssadd (entlast) currobj))
(command "_layer" "set" "nitride" "")
(setq coords (list 
(list 3520.2625 382.9939) 
(list 3520.5625 392.9939) 
(list 3520.5625 392.9939) 
(list 3520.5625 393.9939) 
(list 3594.585 393.2439) 
(list 3594.585 398.1869) 
(list 3520.5625 397.4369) 
(list 3520.5625 398.4369) 
(list 3520.5625 398.4369) 
(list 3520.2625 408.4369) 
(list 3519.7375 408.4369) 
(list 3519.4375 398.4369) 
(list 3519.4375 398.4369) 
(list 3519.4375 397.4369) 
(list 3445.415 398.1869) 
(list 3445.415 393.2439) 
(list 3519.4375 393.9939) 
(list 3519.4375 392.9939) 
(list 3519.4375 392.9939) 
(list 3519.7375 382.9939)))
(apply 'command (append '("pline") coords '("c")))
(setq currobj (ssadd (entlast) currobj))
(command "_layer" "set" "prebias" "")
(setq coords (list 
(list 3519.4375 382.9939) 
(list 3519.4375 393.9939) 
(list 3445.415 393.2439) 
(list 3445.415 398.1869) 
(list 3519.4375 397.4369) 
(list 3519.4375 408.4369) 
(list 3520.5625 408.4369) 
(list 3520.5625 397.4369) 
(list 3594.585 398.1869) 
(list 3594.585 393.2439) 
(list 3520.5625 393.9939) 
(list 3520.5625 382.9939)))
(apply 'command (append '("pline") coords '("c")))
(setq currobj (ssadd (entlast) currobj))
(command "_layer" "set" "nitride" "")
(command "_layer" "set" "fda1" "")
(setq coords (list 
(list 3520.5625 394.1369) 
(list 3594.585 393.3869) 
(list 3594.585 393.5639) 
(list 3520.5625 394.2139)))
(apply 'command (append '("pline") coords '("c")))
(setq currobj (ssadd (entlast) currobj))
(setq coords (list 
(list 3520.5625 394.3569) 
(list 3594.585 393.7069) 
(list 3594.585 393.8839) 
(list 3520.5625 394.4339)))
(apply 'command (append '("pline") coords '("c")))
(setq currobj (ssadd (entlast) currobj))
(setq coords (list 
(list 3520.5625 394.5769) 
(list 3594.585 394.0269) 
(list 3594.585 394.2039) 
(list 3520.5625 394.6539)))
(apply 'command (append '("pline") coords '("c")))
(setq currobj (ssadd (entlast) currobj))
(setq coords (list 
(list 3520.5625 394.7969) 
(list 3594.585 394.3469) 
(list 3594.585 394.5239) 
(list 3520.5625 394.8739)))
(apply 'command (append '("pline") coords '("c")))
(setq currobj (ssadd (entlast) currobj))
(setq coords (list 
(list 3520.5625 395.0169) 
(list 3594.585 394.6669) 
(list 3594.585 394.8439) 
(list 3520.5625 395.0939)))
(apply 'command (append '("pline") coords '("c")))
(setq currobj (ssadd (entlast) currobj))
(setq coords (list 
(list 3520.5625 395.2369) 
(list 3594.585 394.9869) 
(list 3594.585 395.1639) 
(list 3520.5625 395.3139)))
(apply 'command (append '("pline") coords '("c")))
(setq currobj (ssadd (entlast) currobj))
(setq coords (list 
(list 3520.5625 395.4569) 
(list 3594.585 395.3069) 
(list 3594.585 395.4839) 
(list 3520.5625 395.5339)))
(apply 'command (append '("pline") coords '("c")))
(setq currobj (ssadd (entlast) currobj))
(setq coords (list 
(list 3520.5625 395.6769) 
(list 3594.585 395.6269) 
(list 3594.585 395.8039) 
(list 3520.5625 395.7539)))
(apply 'command (append '("pline") coords '("c")))
(setq currobj (ssadd (entlast) currobj))
(setq coords (list 
(list 3520.5625 395.8969) 
(list 3594.585 395.9469) 
(list 3594.585 396.1239) 
(list 3520.5625 395.9739)))
(apply 'command (append '("pline") coords '("c")))
(setq currobj (ssadd (entlast) currobj))
(setq coords (list 
(list 3520.5625 396.1169) 
(list 3594.585 396.2669) 
(list 3594.585 396.4439) 
(list 3520.5625 396.1939)))
(apply 'command (append '("pline") coords '("c")))
(setq currobj (ssadd (entlast) currobj))
(setq coords (list 
(list 3520.5625 396.3369) 
(list 3594.585 396.5869) 
(list 3594.585 396.7639) 
(list 3520.5625 396.4139)))
(apply 'command (append '("pline") coords '("c")))
(setq currobj (ssadd (entlast) currobj))
(setq coords (list 
(list 3520.5625 396.5569) 
(list 3594.585 396.9069) 
(list 3594.585 397.0839) 
(list 3520.5625 396.6339)))
(apply 'command (append '("pline") coords '("c")))
(setq currobj (ssadd (entlast) currobj))
(setq coords (list 
(list 3520.5625 396.7769) 
(list 3594.585 397.2269) 
(list 3594.585 397.4039) 
(list 3520.5625 396.8539)))
(apply 'command (append '("pline") coords '("c")))
(setq currobj (ssadd (entlast) currobj))
(setq coords (list 
(list 3520.5625 396.9969) 
(list 3594.585 397.5469) 
(list 3594.585 397.7239) 
(list 3520.5625 397.0739)))
(apply 'command (append '("pline") coords '("c")))
(setq currobj (ssadd (entlast) currobj))
(setq coords (list 
(list 3520.5625 397.2169) 
(list 3594.585 397.8669) 
(list 3594.585 398.0439) 
(list 3520.5625 397.2939)))
(apply 'command (append '("pline") coords '("c")))
(setq currobj (ssadd (entlast) currobj))
(setq coords (list 
(list 3519.4375 397.2939) 
(list 3445.415 398.0439) 
(list 3445.415 397.8669) 
(list 3519.4375 397.2169)))
(apply 'command (append '("pline") coords '("c")))
(setq currobj (ssadd (entlast) currobj))
(setq coords (list 
(list 3519.4375 397.0739) 
(list 3445.415 397.7239) 
(list 3445.415 397.5469) 
(list 3519.4375 396.9969)))
(apply 'command (append '("pline") coords '("c")))
(setq currobj (ssadd (entlast) currobj))
(setq coords (list 
(list 3519.4375 396.8539) 
(list 3445.415 397.4039) 
(list 3445.415 397.2269) 
(list 3519.4375 396.7769)))
(apply 'command (append '("pline") coords '("c")))
(setq currobj (ssadd (entlast) currobj))
(setq coords (list 
(list 3519.4375 396.6339) 
(list 3445.415 397.0839) 
(list 3445.415 396.9069) 
(list 3519.4375 396.5569)))
(apply 'command (append '("pline") coords '("c")))
(setq currobj (ssadd (entlast) currobj))
(setq coords (list 
(list 3519.4375 396.4139) 
(list 3445.415 396.7639) 
(list 3445.415 396.5869) 
(list 3519.4375 396.3369)))
(apply 'command (append '("pline") coords '("c")))
(setq currobj (ssadd (entlast) currobj))
(setq coords (list 
(list 3519.4375 396.1939) 
(list 3445.415 396.4439) 
(list 3445.415 396.2669) 
(list 3519.4375 396.1169)))
(apply 'command (append '("pline") coords '("c")))
(setq currobj (ssadd (entlast) currobj))
(setq coords (list 
(list 3519.4375 395.9739) 
(list 3445.415 396.1239) 
(list 3445.415 395.9469) 
(list 3519.4375 395.8969)))
(apply 'command (append '("pline") coords '("c")))
(setq currobj (ssadd (entlast) currobj))
(setq coords (list 
(list 3519.4375 395.7539) 
(list 3445.415 395.8039) 
(list 3445.415 395.6269) 
(list 3519.4375 395.6769)))
(apply 'command (append '("pline") coords '("c")))
(setq currobj (ssadd (entlast) currobj))
(setq coords (list 
(list 3519.4375 395.5339) 
(list 3445.415 395.4839) 
(list 3445.415 395.3069) 
(list 3519.4375 395.4569)))
(apply 'command (append '("pline") coords '("c")))
(setq currobj (ssadd (entlast) currobj))
(setq coords (list 
(list 3519.4375 395.3139) 
(list 3445.415 395.1639) 
(list 3445.415 394.9869) 
(list 3519.4375 395.2369)))
(apply 'command (append '("pline") coords '("c")))
(setq currobj (ssadd (entlast) currobj))
(setq coords (list 
(list 3519.4375 395.0939) 
(list 3445.415 394.8439) 
(list 3445.415 394.6669) 
(list 3519.4375 395.0169)))
(apply 'command (append '("pline") coords '("c")))
(setq currobj (ssadd (entlast) currobj))
(setq coords (list 
(list 3519.4375 394.8739) 
(list 3445.415 394.5239) 
(list 3445.415 394.3469) 
(list 3519.4375 394.7969)))
(apply 'command (append '("pline") coords '("c")))
(setq currobj (ssadd (entlast) currobj))
(setq coords (list 
(list 3519.4375 394.6539) 
(list 3445.415 394.2039) 
(list 3445.415 394.0269) 
(list 3519.4375 394.5769)))
(apply 'command (append '("pline") coords '("c")))
(setq currobj (ssadd (entlast) currobj))
(setq coords (list 
(list 3519.4375 394.4339) 
(list 3445.415 393.8839) 
(list 3445.415 393.7069) 
(list 3519.4375 394.3569)))
(apply 'command (append '("pline") coords '("c")))
(setq currobj (ssadd (entlast) currobj))
(setq coords (list 
(list 3519.4375 394.2139) 
(list 3445.415 393.5639) 
(list 3445.415 393.3869) 
(list 3519.4375 394.1369)))
(apply 'command (append '("pline") coords '("c")))
(setq currobj (ssadd (entlast) currobj))
(command "_layer" "set" "nitride" "")
(command "_layer" "set" "text" "")
(command "_circle" "3519.0625,382.9939" "0.075")
(command "_circle" "3519.0625,383.2939" "0.075")
(command "_circle" "3519.0625,383.5939" "0.075")
(command "_circle" "3519.0625,383.8939" "0.075")
(command "_circle" "3519.0625,384.1939" "0.075")
(command "_circle" "3518.7625,382.9939" "0.075")
(command "_circle" "3518.7625,383.2939" "0.075")
(command "_circle" "3518.7625,383.5939" "0.075")
(command "_circle" "3518.7625,383.8939" "0.075")
(command "_circle" "3518.7625,384.1939" "0.075")
(command "_circle" "3518.4625,382.9939" "0.075")
(command "_circle" "3518.4625,383.2939" "0.075")
(command "_circle" "3518.4625,383.5939" "0.075")
(command "_circle" "3518.4625,383.8939" "0.075")
(command "_circle" "3518.4625,384.1939" "0.075")
(command "_circle" "3518.1625,382.9939" "0.075")
(command "_circle" "3518.1625,383.2939" "0.075")
(command "_circle" "3518.1625,383.5939" "0.075")
(command "_circle" "3518.1625,383.8939" "0.075")
(command "_circle" "3518.1625,384.1939" "0.075")
(command "_circle" "3517.8625,382.9939" "0.075")
(command "_circle" "3517.8625,383.2939" "0.075")
(command "_circle" "3517.8625,383.5939" "0.075")
(command "_circle" "3517.8625,383.8939" "0.075")
(command "_circle" "3517.8625,384.1939" "0.075")
(command "_layer" "set" "nitride" "")
(setq coords (list 
(list 3520.2625 408.4369) 
(list 3520.2625 524.0816) 
(list 3519.7375 524.0816) 
(list 3519.7375 408.4369)))
(apply 'command (append '("pline") coords '("c")))
(setq currobj (ssadd (entlast) currobj))
(command "_layer" "set" "prebias" "")
(command "_rectangle" "3519.7375,408.4369" "3520.2625,524.0816")
(setq currobj (ssadd (entlast) currobj))
(command "_layer" "set" "nitride" "")
(setq coords (list 
(list 3520.2625 524.0816) 
(list 3520.5625 534.0816) 
(list 3520.5625 534.0816) 
(list 3520.5625 535.0816) 
(list 3594.585 534.3316) 
(list 3594.585 539.2746) 
(list 3520.5625 538.5246) 
(list 3520.5625 539.5246) 
(list 3520.5625 539.5246) 
(list 3520.2625 549.5246) 
(list 3519.7375 549.5246) 
(list 3519.4375 539.5246) 
(list 3519.4375 539.5246) 
(list 3519.4375 538.5246) 
(list 3445.415 539.2746) 
(list 3445.415 534.3316) 
(list 3519.4375 535.0816) 
(list 3519.4375 534.0816) 
(list 3519.4375 534.0816) 
(list 3519.7375 524.0816)))
(apply 'command (append '("pline") coords '("c")))
(setq currobj (ssadd (entlast) currobj))
(command "_layer" "set" "prebias" "")
(setq coords (list 
(list 3519.4375 524.0816) 
(list 3519.4375 535.0816) 
(list 3445.415 534.3316) 
(list 3445.415 539.2746) 
(list 3519.4375 538.5246) 
(list 3519.4375 549.5246) 
(list 3520.5625 549.5246) 
(list 3520.5625 538.5246) 
(list 3594.585 539.2746) 
(list 3594.585 534.3316) 
(list 3520.5625 535.0816) 
(list 3520.5625 524.0816)))
(apply 'command (append '("pline") coords '("c")))
(setq currobj (ssadd (entlast) currobj))
(command "_layer" "set" "nitride" "")
(command "_layer" "set" "fda1" "")
(setq coords (list 
(list 3520.5625 535.2246) 
(list 3594.585 534.4746) 
(list 3594.585 534.6516) 
(list 3520.5625 535.3016)))
(apply 'command (append '("pline") coords '("c")))
(setq currobj (ssadd (entlast) currobj))
(setq coords (list 
(list 3520.5625 535.4446) 
(list 3594.585 534.7946) 
(list 3594.585 534.9716) 
(list 3520.5625 535.5216)))
(apply 'command (append '("pline") coords '("c")))
(setq currobj (ssadd (entlast) currobj))
(setq coords (list 
(list 3520.5625 535.6646) 
(list 3594.585 535.1146) 
(list 3594.585 535.2916) 
(list 3520.5625 535.7416)))
(apply 'command (append '("pline") coords '("c")))
(setq currobj (ssadd (entlast) currobj))
(setq coords (list 
(list 3520.5625 535.8846) 
(list 3594.585 535.4346) 
(list 3594.585 535.6116) 
(list 3520.5625 535.9616)))
(apply 'command (append '("pline") coords '("c")))
(setq currobj (ssadd (entlast) currobj))
(setq coords (list 
(list 3520.5625 536.1046) 
(list 3594.585 535.7546) 
(list 3594.585 535.9316) 
(list 3520.5625 536.1816)))
(apply 'command (append '("pline") coords '("c")))
(setq currobj (ssadd (entlast) currobj))
(setq coords (list 
(list 3520.5625 536.3246) 
(list 3594.585 536.0746) 
(list 3594.585 536.2516) 
(list 3520.5625 536.4016)))
(apply 'command (append '("pline") coords '("c")))
(setq currobj (ssadd (entlast) currobj))
(setq coords (list 
(list 3520.5625 536.5446) 
(list 3594.585 536.3946) 
(list 3594.585 536.5716) 
(list 3520.5625 536.6216)))
(apply 'command (append '("pline") coords '("c")))
(setq currobj (ssadd (entlast) currobj))
(setq coords (list 
(list 3520.5625 536.7646) 
(list 3594.585 536.7146) 
(list 3594.585 536.8916) 
(list 3520.5625 536.8416)))
(apply 'command (append '("pline") coords '("c")))
(setq currobj (ssadd (entlast) currobj))
(setq coords (list 
(list 3520.5625 536.9846) 
(list 3594.585 537.0346) 
(list 3594.585 537.2116) 
(list 3520.5625 537.0616)))
(apply 'command (append '("pline") coords '("c")))
(setq currobj (ssadd (entlast) currobj))
(setq coords (list 
(list 3520.5625 537.2046) 
(list 3594.585 537.3546) 
(list 3594.585 537.5316) 
(list 3520.5625 537.2816)))
(apply 'command (append '("pline") coords '("c")))
(setq currobj (ssadd (entlast) currobj))
(setq coords (list 
(list 3520.5625 537.4246) 
(list 3594.585 537.6746) 
(list 3594.585 537.8516) 
(list 3520.5625 537.5016)))
(apply 'command (append '("pline") coords '("c")))
(setq currobj (ssadd (entlast) currobj))
(setq coords (list 
(list 3520.5625 537.6446) 
(list 3594.585 537.9946) 
(list 3594.585 538.1716) 
(list 3520.5625 537.7216)))
(apply 'command (append '("pline") coords '("c")))
(setq currobj (ssadd (entlast) currobj))
(setq coords (list 
(list 3520.5625 537.8646) 
(list 3594.585 538.3146) 
(list 3594.585 538.4916) 
(list 3520.5625 537.9416)))
(apply 'command (append '("pline") coords '("c")))
(setq currobj (ssadd (entlast) currobj))
(setq coords (list 
(list 3520.5625 538.0846) 
(list 3594.585 538.6346) 
(list 3594.585 538.8116) 
(list 3520.5625 538.1616)))
(apply 'command (append '("pline") coords '("c")))
(setq currobj (ssadd (entlast) currobj))
(setq coords (list 
(list 3520.5625 538.3046) 
(list 3594.585 538.9546) 
(list 3594.585 539.1316) 
(list 3520.5625 538.3816)))
(apply 'command (append '("pline") coords '("c")))
(setq currobj (ssadd (entlast) currobj))
(setq coords (list 
(list 3519.4375 538.3816) 
(list 3445.415 539.1316) 
(list 3445.415 538.9546) 
(list 3519.4375 538.3046)))
(apply 'command (append '("pline") coords '("c")))
(setq currobj (ssadd (entlast) currobj))
(setq coords (list 
(list 3519.4375 538.1616) 
(list 3445.415 538.8116) 
(list 3445.415 538.6346) 
(list 3519.4375 538.0846)))
(apply 'command (append '("pline") coords '("c")))
(setq currobj (ssadd (entlast) currobj))
(setq coords (list 
(list 3519.4375 537.9416) 
(list 3445.415 538.4916) 
(list 3445.415 538.3146) 
(list 3519.4375 537.8646)))
(apply 'command (append '("pline") coords '("c")))
(setq currobj (ssadd (entlast) currobj))
(setq coords (list 
(list 3519.4375 537.7216) 
(list 3445.415 538.1716) 
(list 3445.415 537.9946) 
(list 3519.4375 537.6446)))
(apply 'command (append '("pline") coords '("c")))
(setq currobj (ssadd (entlast) currobj))
(setq coords (list 
(list 3519.4375 537.5016) 
(list 3445.415 537.8516) 
(list 3445.415 537.6746) 
(list 3519.4375 537.4246)))
(apply 'command (append '("pline") coords '("c")))
(setq currobj (ssadd (entlast) currobj))
(setq coords (list 
(list 3519.4375 537.2816) 
(list 3445.415 537.5316) 
(list 3445.415 537.3546) 
(list 3519.4375 537.2046)))
(apply 'command (append '("pline") coords '("c")))
(setq currobj (ssadd (entlast) currobj))
(setq coords (list 
(list 3519.4375 537.0616) 
(list 3445.415 537.2116) 
(list 3445.415 537.0346) 
(list 3519.4375 536.9846)))
(apply 'command (append '("pline") coords '("c")))
(setq currobj (ssadd (entlast) currobj))
(setq coords (list 
(list 3519.4375 536.8416) 
(list 3445.415 536.8916) 
(list 3445.415 536.7146) 
(list 3519.4375 536.7646)))
(apply 'command (append '("pline") coords '("c")))
(setq currobj (ssadd (entlast) currobj))
(setq coords (list 
(list 3519.4375 536.6216) 
(list 3445.415 536.5716) 
(list 3445.415 536.3946) 
(list 3519.4375 536.5446)))
(apply 'command (append '("pline") coords '("c")))
(setq currobj (ssadd (entlast) currobj))
(setq coords (list 
(list 3519.4375 536.4016) 
(list 3445.415 536.2516) 
(list 3445.415 536.0746) 
(list 3519.4375 536.3246)))
(apply 'command (append '("pline") coords '("c")))
(setq currobj (ssadd (entlast) currobj))
(setq coords (list 
(list 3519.4375 536.1816) 
(list 3445.415 535.9316) 
(list 3445.415 535.7546) 
(list 3519.4375 536.1046)))
(apply 'command (append '("pline") coords '("c")))
(setq currobj (ssadd (entlast) currobj))
(setq coords (list 
(list 3519.4375 535.9616) 
(list 3445.415 535.6116) 
(list 3445.415 535.4346) 
(list 3519.4375 535.8846)))
(apply 'command (append '("pline") coords '("c")))
(setq currobj (ssadd (entlast) currobj))
(setq coords (list 
(list 3519.4375 535.7416) 
(list 3445.415 535.2916) 
(list 3445.415 535.1146) 
(list 3519.4375 535.6646)))
(apply 'command (append '("pline") coords '("c")))
(setq currobj (ssadd (entlast) currobj))
(setq coords (list 
(list 3519.4375 535.5216) 
(list 3445.415 534.9716) 
(list 3445.415 534.7946) 
(list 3519.4375 535.4446)))
(apply 'command (append '("pline") coords '("c")))
(setq currobj (ssadd (entlast) currobj))
(setq coords (list 
(list 3519.4375 535.3016) 
(list 3445.415 534.6516) 
(list 3445.415 534.4746) 
(list 3519.4375 535.2246)))
(apply 'command (append '("pline") coords '("c")))
(setq currobj (ssadd (entlast) currobj))
(command "_layer" "set" "nitride" "")
(command "_layer" "set" "text" "")
(command "_circle" "3519.0625,524.0816" "0.075")
(command "_circle" "3519.0625,524.3816" "0.075")
(command "_circle" "3519.0625,524.6816" "0.075")
(command "_circle" "3519.0625,524.9816" "0.075")
(command "_circle" "3519.0625,525.2816" "0.075")
(command "_circle" "3518.7625,524.0816" "0.075")
(command "_circle" "3518.7625,524.3816" "0.075")
(command "_circle" "3518.7625,524.6816" "0.075")
(command "_circle" "3518.7625,524.9816" "0.075")
(command "_circle" "3518.7625,525.2816" "0.075")
(command "_circle" "3518.4625,524.0816" "0.075")
(command "_circle" "3518.4625,524.3816" "0.075")
(command "_circle" "3518.4625,524.6816" "0.075")
(command "_circle" "3518.4625,524.9816" "0.075")
(command "_circle" "3518.4625,525.2816" "0.075")
(command "_circle" "3518.1625,524.0816" "0.075")
(command "_circle" "3518.1625,524.3816" "0.075")
(command "_circle" "3518.1625,524.6816" "0.075")
(command "_circle" "3518.1625,524.9816" "0.075")
(command "_circle" "3518.1625,525.2816" "0.075")
(command "_circle" "3517.8625,524.0816" "0.075")
(command "_circle" "3517.8625,524.3816" "0.075")
(command "_circle" "3517.8625,524.6816" "0.075")
(command "_circle" "3517.8625,524.9816" "0.075")
(command "_circle" "3517.8625,525.2816" "0.075")
(command "_layer" "set" "nitride" "")
(setq coords (list 
(list 3520.2625 549.5246) 
(list 3520.2625 665.1693) 
(list 3519.7375 665.1693) 
(list 3519.7375 549.5246)))
(apply 'command (append '("pline") coords '("c")))
(setq currobj (ssadd (entlast) currobj))
(command "_layer" "set" "prebias" "")
(command "_rectangle" "3519.7375,549.5246" "3520.2625,665.1693")
(setq currobj (ssadd (entlast) currobj))
(command "_layer" "set" "nitride" "")
(setq coords (list 
(list 3520.2625 665.1693) 
(list 3520.5625 675.1693) 
(list 3520.5625 675.1693) 
(list 3520.5625 676.1693) 
(list 3594.585 675.4193) 
(list 3594.585 680.3623) 
(list 3520.5625 679.6123) 
(list 3520.5625 680.6123) 
(list 3520.5625 680.6123) 
(list 3520.2625 690.6123) 
(list 3519.7375 690.6123) 
(list 3519.4375 680.6123) 
(list 3519.4375 680.6123) 
(list 3519.4375 679.6123) 
(list 3445.415 680.3623) 
(list 3445.415 675.4193) 
(list 3519.4375 676.1693) 
(list 3519.4375 675.1693) 
(list 3519.4375 675.1693) 
(list 3519.7375 665.1693)))
(apply 'command (append '("pline") coords '("c")))
(setq currobj (ssadd (entlast) currobj))
(command "_layer" "set" "prebias" "")
(setq coords (list 
(list 3519.4375 665.1693) 
(list 3519.4375 676.1693) 
(list 3445.415 675.4193) 
(list 3445.415 680.3623) 
(list 3519.4375 679.6123) 
(list 3519.4375 690.6123) 
(list 3520.5625 690.6123) 
(list 3520.5625 679.6123) 
(list 3594.585 680.3623) 
(list 3594.585 675.4193) 
(list 3520.5625 676.1693) 
(list 3520.5625 665.1693)))
(apply 'command (append '("pline") coords '("c")))
(setq currobj (ssadd (entlast) currobj))
(command "_layer" "set" "nitride" "")
(command "_layer" "set" "fda1" "")
(setq coords (list 
(list 3520.5625 676.3123) 
(list 3594.585 675.5623) 
(list 3594.585 675.7393) 
(list 3520.5625 676.3893)))
(apply 'command (append '("pline") coords '("c")))
(setq currobj (ssadd (entlast) currobj))
(setq coords (list 
(list 3520.5625 676.5323) 
(list 3594.585 675.8823) 
(list 3594.585 676.0593) 
(list 3520.5625 676.6093)))
(apply 'command (append '("pline") coords '("c")))
(setq currobj (ssadd (entlast) currobj))
(setq coords (list 
(list 3520.5625 676.7523) 
(list 3594.585 676.2023) 
(list 3594.585 676.3793) 
(list 3520.5625 676.8293)))
(apply 'command (append '("pline") coords '("c")))
(setq currobj (ssadd (entlast) currobj))
(setq coords (list 
(list 3520.5625 676.9723) 
(list 3594.585 676.5223) 
(list 3594.585 676.6993) 
(list 3520.5625 677.0493)))
(apply 'command (append '("pline") coords '("c")))
(setq currobj (ssadd (entlast) currobj))
(setq coords (list 
(list 3520.5625 677.1923) 
(list 3594.585 676.8423) 
(list 3594.585 677.0193) 
(list 3520.5625 677.2693)))
(apply 'command (append '("pline") coords '("c")))
(setq currobj (ssadd (entlast) currobj))
(setq coords (list 
(list 3520.5625 677.4123) 
(list 3594.585 677.1623) 
(list 3594.585 677.3393) 
(list 3520.5625 677.4893)))
(apply 'command (append '("pline") coords '("c")))
(setq currobj (ssadd (entlast) currobj))
(setq coords (list 
(list 3520.5625 677.6323) 
(list 3594.585 677.4823) 
(list 3594.585 677.6593) 
(list 3520.5625 677.7093)))
(apply 'command (append '("pline") coords '("c")))
(setq currobj (ssadd (entlast) currobj))
(setq coords (list 
(list 3520.5625 677.8523) 
(list 3594.585 677.8023) 
(list 3594.585 677.9793) 
(list 3520.5625 677.9293)))
(apply 'command (append '("pline") coords '("c")))
(setq currobj (ssadd (entlast) currobj))
(setq coords (list 
(list 3520.5625 678.0723) 
(list 3594.585 678.1223) 
(list 3594.585 678.2993) 
(list 3520.5625 678.1493)))
(apply 'command (append '("pline") coords '("c")))
(setq currobj (ssadd (entlast) currobj))
(setq coords (list 
(list 3520.5625 678.2923) 
(list 3594.585 678.4423) 
(list 3594.585 678.6193) 
(list 3520.5625 678.3693)))
(apply 'command (append '("pline") coords '("c")))
(setq currobj (ssadd (entlast) currobj))
(setq coords (list 
(list 3520.5625 678.5123) 
(list 3594.585 678.7623) 
(list 3594.585 678.9393) 
(list 3520.5625 678.5893)))
(apply 'command (append '("pline") coords '("c")))
(setq currobj (ssadd (entlast) currobj))
(setq coords (list 
(list 3520.5625 678.7323) 
(list 3594.585 679.0823) 
(list 3594.585 679.2593) 
(list 3520.5625 678.8093)))
(apply 'command (append '("pline") coords '("c")))
(setq currobj (ssadd (entlast) currobj))
(setq coords (list 
(list 3520.5625 678.9523) 
(list 3594.585 679.4023) 
(list 3594.585 679.5793) 
(list 3520.5625 679.0293)))
(apply 'command (append '("pline") coords '("c")))
(setq currobj (ssadd (entlast) currobj))
(setq coords (list 
(list 3520.5625 679.1723) 
(list 3594.585 679.7223) 
(list 3594.585 679.8993) 
(list 3520.5625 679.2493)))
(apply 'command (append '("pline") coords '("c")))
(setq currobj (ssadd (entlast) currobj))
(setq coords (list 
(list 3520.5625 679.3923) 
(list 3594.585 680.0423) 
(list 3594.585 680.2193) 
(list 3520.5625 679.4693)))
(apply 'command (append '("pline") coords '("c")))
(setq currobj (ssadd (entlast) currobj))
(setq coords (list 
(list 3519.4375 679.4693) 
(list 3445.415 680.2193) 
(list 3445.415 680.0423) 
(list 3519.4375 679.3923)))
(apply 'command (append '("pline") coords '("c")))
(setq currobj (ssadd (entlast) currobj))
(setq coords (list 
(list 3519.4375 679.2493) 
(list 3445.415 679.8993) 
(list 3445.415 679.7223) 
(list 3519.4375 679.1723)))
(apply 'command (append '("pline") coords '("c")))
(setq currobj (ssadd (entlast) currobj))
(setq coords (list 
(list 3519.4375 679.0293) 
(list 3445.415 679.5793) 
(list 3445.415 679.4023) 
(list 3519.4375 678.9523)))
(apply 'command (append '("pline") coords '("c")))
(setq currobj (ssadd (entlast) currobj))
(setq coords (list 
(list 3519.4375 678.8093) 
(list 3445.415 679.2593) 
(list 3445.415 679.0823) 
(list 3519.4375 678.7323)))
(apply 'command (append '("pline") coords '("c")))
(setq currobj (ssadd (entlast) currobj))
(setq coords (list 
(list 3519.4375 678.5893) 
(list 3445.415 678.9393) 
(list 3445.415 678.7623) 
(list 3519.4375 678.5123)))
(apply 'command (append '("pline") coords '("c")))
(setq currobj (ssadd (entlast) currobj))
(setq coords (list 
(list 3519.4375 678.3693) 
(list 3445.415 678.6193) 
(list 3445.415 678.4423) 
(list 3519.4375 678.2923)))
(apply 'command (append '("pline") coords '("c")))
(setq currobj (ssadd (entlast) currobj))
(setq coords (list 
(list 3519.4375 678.1493) 
(list 3445.415 678.2993) 
(list 3445.415 678.1223) 
(list 3519.4375 678.0723)))
(apply 'command (append '("pline") coords '("c")))
(setq currobj (ssadd (entlast) currobj))
(setq coords (list 
(list 3519.4375 677.9293) 
(list 3445.415 677.9793) 
(list 3445.415 677.8023) 
(list 3519.4375 677.8523)))
(apply 'command (append '("pline") coords '("c")))
(setq currobj (ssadd (entlast) currobj))
(setq coords (list 
(list 3519.4375 677.7093) 
(list 3445.415 677.6593) 
(list 3445.415 677.4823) 
(list 3519.4375 677.6323)))
(apply 'command (append '("pline") coords '("c")))
(setq currobj (ssadd (entlast) currobj))
(setq coords (list 
(list 3519.4375 677.4893) 
(list 3445.415 677.3393) 
(list 3445.415 677.1623) 
(list 3519.4375 677.4123)))
(apply 'command (append '("pline") coords '("c")))
(setq currobj (ssadd (entlast) currobj))
(setq coords (list 
(list 3519.4375 677.2693) 
(list 3445.415 677.0193) 
(list 3445.415 676.8423) 
(list 3519.4375 677.1923)))
(apply 'command (append '("pline") coords '("c")))
(setq currobj (ssadd (entlast) currobj))
(setq coords (list 
(list 3519.4375 677.0493) 
(list 3445.415 676.6993) 
(list 3445.415 676.5223) 
(list 3519.4375 676.9723)))
(apply 'command (append '("pline") coords '("c")))
(setq currobj (ssadd (entlast) currobj))
(setq coords (list 
(list 3519.4375 676.8293) 
(list 3445.415 676.3793) 
(list 3445.415 676.2023) 
(list 3519.4375 676.7523)))
(apply 'command (append '("pline") coords '("c")))
(setq currobj (ssadd (entlast) currobj))
(setq coords (list 
(list 3519.4375 676.6093) 
(list 3445.415 676.0593) 
(list 3445.415 675.8823) 
(list 3519.4375 676.5323)))
(apply 'command (append '("pline") coords '("c")))
(setq currobj (ssadd (entlast) currobj))
(setq coords (list 
(list 3519.4375 676.3893) 
(list 3445.415 675.7393) 
(list 3445.415 675.5623) 
(list 3519.4375 676.3123)))
(apply 'command (append '("pline") coords '("c")))
(setq currobj (ssadd (entlast) currobj))
(command "_layer" "set" "nitride" "")
(command "_layer" "set" "text" "")
(command "_circle" "3519.0625,665.1693" "0.075")
(command "_circle" "3519.0625,665.4693" "0.075")
(command "_circle" "3519.0625,665.7693" "0.075")
(command "_circle" "3519.0625,666.0693" "0.075")
(command "_circle" "3519.0625,666.3693" "0.075")
(command "_circle" "3518.7625,665.1693" "0.075")
(command "_circle" "3518.7625,665.4693" "0.075")
(command "_circle" "3518.7625,665.7693" "0.075")
(command "_circle" "3518.7625,666.0693" "0.075")
(command "_circle" "3518.7625,666.3693" "0.075")
(command "_circle" "3518.4625,665.1693" "0.075")
(command "_circle" "3518.4625,665.4693" "0.075")
(command "_circle" "3518.4625,665.7693" "0.075")
(command "_circle" "3518.4625,666.0693" "0.075")
(command "_circle" "3518.4625,666.3693" "0.075")
(command "_circle" "3518.1625,665.1693" "0.075")
(command "_circle" "3518.1625,665.4693" "0.075")
(command "_circle" "3518.1625,665.7693" "0.075")
(command "_circle" "3518.1625,666.0693" "0.075")
(command "_circle" "3518.1625,666.3693" "0.075")
(command "_circle" "3517.8625,665.1693" "0.075")
(command "_circle" "3517.8625,665.4693" "0.075")
(command "_circle" "3517.8625,665.7693" "0.075")
(command "_circle" "3517.8625,666.0693" "0.075")
(command "_circle" "3517.8625,666.3693" "0.075")
(command "_layer" "set" "nitride" "")
(setq coords (list 
(list 3520.2625 690.6123) 
(list 3520.2625 806.257) 
(list 3519.7375 806.257) 
(list 3519.7375 690.6123)))
(apply 'command (append '("pline") coords '("c")))
(setq currobj (ssadd (entlast) currobj))
(command "_layer" "set" "prebias" "")
(command "_rectangle" "3519.7375,690.6123" "3520.2625,806.257")
(setq currobj (ssadd (entlast) currobj))
(command "_layer" "set" "nitride" "")
(setq coords (list 
(list 3520.2625 806.257) 
(list 3520.5625 816.257) 
(list 3520.5625 816.257) 
(list 3520.5625 817.257) 
(list 3594.585 816.507) 
(list 3594.585 821.45) 
(list 3520.5625 820.7) 
(list 3520.5625 821.7) 
(list 3520.5625 821.7) 
(list 3520.2625 831.7) 
(list 3519.7375 831.7) 
(list 3519.4375 821.7) 
(list 3519.4375 821.7) 
(list 3519.4375 820.7) 
(list 3445.415 821.45) 
(list 3445.415 816.507) 
(list 3519.4375 817.257) 
(list 3519.4375 816.257) 
(list 3519.4375 816.257) 
(list 3519.7375 806.257)))
(apply 'command (append '("pline") coords '("c")))
(setq currobj (ssadd (entlast) currobj))
(command "_layer" "set" "prebias" "")
(setq coords (list 
(list 3519.4375 806.257) 
(list 3519.4375 817.257) 
(list 3445.415 816.507) 
(list 3445.415 821.45) 
(list 3519.4375 820.7) 
(list 3519.4375 831.7) 
(list 3520.5625 831.7) 
(list 3520.5625 820.7) 
(list 3594.585 821.45) 
(list 3594.585 816.507) 
(list 3520.5625 817.257) 
(list 3520.5625 806.257)))
(apply 'command (append '("pline") coords '("c")))
(setq currobj (ssadd (entlast) currobj))
(command "_layer" "set" "nitride" "")
(command "_layer" "set" "fda1" "")
(setq coords (list 
(list 3520.5625 817.4) 
(list 3594.585 816.65) 
(list 3594.585 816.827) 
(list 3520.5625 817.477)))
(apply 'command (append '("pline") coords '("c")))
(setq currobj (ssadd (entlast) currobj))
(setq coords (list 
(list 3520.5625 817.62) 
(list 3594.585 816.97) 
(list 3594.585 817.147) 
(list 3520.5625 817.697)))
(apply 'command (append '("pline") coords '("c")))
(setq currobj (ssadd (entlast) currobj))
(setq coords (list 
(list 3520.5625 817.84) 
(list 3594.585 817.29) 
(list 3594.585 817.467) 
(list 3520.5625 817.917)))
(apply 'command (append '("pline") coords '("c")))
(setq currobj (ssadd (entlast) currobj))
(setq coords (list 
(list 3520.5625 818.06) 
(list 3594.585 817.61) 
(list 3594.585 817.787) 
(list 3520.5625 818.137)))
(apply 'command (append '("pline") coords '("c")))
(setq currobj (ssadd (entlast) currobj))
(setq coords (list 
(list 3520.5625 818.28) 
(list 3594.585 817.93) 
(list 3594.585 818.107) 
(list 3520.5625 818.357)))
(apply 'command (append '("pline") coords '("c")))
(setq currobj (ssadd (entlast) currobj))
(setq coords (list 
(list 3520.5625 818.5) 
(list 3594.585 818.25) 
(list 3594.585 818.427) 
(list 3520.5625 818.577)))
(apply 'command (append '("pline") coords '("c")))
(setq currobj (ssadd (entlast) currobj))
(setq coords (list 
(list 3520.5625 818.72) 
(list 3594.585 818.57) 
(list 3594.585 818.747) 
(list 3520.5625 818.797)))
(apply 'command (append '("pline") coords '("c")))
(setq currobj (ssadd (entlast) currobj))
(setq coords (list 
(list 3520.5625 818.94) 
(list 3594.585 818.89) 
(list 3594.585 819.067) 
(list 3520.5625 819.017)))
(apply 'command (append '("pline") coords '("c")))
(setq currobj (ssadd (entlast) currobj))
(setq coords (list 
(list 3520.5625 819.16) 
(list 3594.585 819.21) 
(list 3594.585 819.387) 
(list 3520.5625 819.237)))
(apply 'command (append '("pline") coords '("c")))
(setq currobj (ssadd (entlast) currobj))
(setq coords (list 
(list 3520.5625 819.38) 
(list 3594.585 819.53) 
(list 3594.585 819.707) 
(list 3520.5625 819.457)))
(apply 'command (append '("pline") coords '("c")))
(setq currobj (ssadd (entlast) currobj))
(setq coords (list 
(list 3520.5625 819.6) 
(list 3594.585 819.85) 
(list 3594.585 820.027) 
(list 3520.5625 819.677)))
(apply 'command (append '("pline") coords '("c")))
(setq currobj (ssadd (entlast) currobj))
(setq coords (list 
(list 3520.5625 819.82) 
(list 3594.585 820.17) 
(list 3594.585 820.347) 
(list 3520.5625 819.897)))
(apply 'command (append '("pline") coords '("c")))
(setq currobj (ssadd (entlast) currobj))
(setq coords (list 
(list 3520.5625 820.04) 
(list 3594.585 820.49) 
(list 3594.585 820.667) 
(list 3520.5625 820.117)))
(apply 'command (append '("pline") coords '("c")))
(setq currobj (ssadd (entlast) currobj))
(setq coords (list 
(list 3520.5625 820.26) 
(list 3594.585 820.81) 
(list 3594.585 820.987) 
(list 3520.5625 820.337)))
(apply 'command (append '("pline") coords '("c")))
(setq currobj (ssadd (entlast) currobj))
(setq coords (list 
(list 3520.5625 820.48) 
(list 3594.585 821.13) 
(list 3594.585 821.307) 
(list 3520.5625 820.557)))
(apply 'command (append '("pline") coords '("c")))
(setq currobj (ssadd (entlast) currobj))
(setq coords (list 
(list 3519.4375 820.557) 
(list 3445.415 821.307) 
(list 3445.415 821.13) 
(list 3519.4375 820.48)))
(apply 'command (append '("pline") coords '("c")))
(setq currobj (ssadd (entlast) currobj))
(setq coords (list 
(list 3519.4375 820.337) 
(list 3445.415 820.987) 
(list 3445.415 820.81) 
(list 3519.4375 820.26)))
(apply 'command (append '("pline") coords '("c")))
(setq currobj (ssadd (entlast) currobj))
(setq coords (list 
(list 3519.4375 820.117) 
(list 3445.415 820.667) 
(list 3445.415 820.49) 
(list 3519.4375 820.04)))
(apply 'command (append '("pline") coords '("c")))
(setq currobj (ssadd (entlast) currobj))
(setq coords (list 
(list 3519.4375 819.897) 
(list 3445.415 820.347) 
(list 3445.415 820.17) 
(list 3519.4375 819.82)))
(apply 'command (append '("pline") coords '("c")))
(setq currobj (ssadd (entlast) currobj))
(setq coords (list 
(list 3519.4375 819.677) 
(list 3445.415 820.027) 
(list 3445.415 819.85) 
(list 3519.4375 819.6)))
(apply 'command (append '("pline") coords '("c")))
(setq currobj (ssadd (entlast) currobj))
(setq coords (list 
(list 3519.4375 819.457) 
(list 3445.415 819.707) 
(list 3445.415 819.53) 
(list 3519.4375 819.38)))
(apply 'command (append '("pline") coords '("c")))
(setq currobj (ssadd (entlast) currobj))
(setq coords (list 
(list 3519.4375 819.237) 
(list 3445.415 819.387) 
(list 3445.415 819.21) 
(list 3519.4375 819.16)))
(apply 'command (append '("pline") coords '("c")))
(setq currobj (ssadd (entlast) currobj))
(setq coords (list 
(list 3519.4375 819.017) 
(list 3445.415 819.067) 
(list 3445.415 818.89) 
(list 3519.4375 818.94)))
(apply 'command (append '("pline") coords '("c")))
(setq currobj (ssadd (entlast) currobj))
(setq coords (list 
(list 3519.4375 818.797) 
(list 3445.415 818.747) 
(list 3445.415 818.57) 
(list 3519.4375 818.72)))
(apply 'command (append '("pline") coords '("c")))
(setq currobj (ssadd (entlast) currobj))
(setq coords (list 
(list 3519.4375 818.577) 
(list 3445.415 818.427) 
(list 3445.415 818.25) 
(list 3519.4375 818.5)))
(apply 'command (append '("pline") coords '("c")))
(setq currobj (ssadd (entlast) currobj))
(setq coords (list 
(list 3519.4375 818.357) 
(list 3445.415 818.107) 
(list 3445.415 817.93) 
(list 3519.4375 818.28)))
(apply 'command (append '("pline") coords '("c")))
(setq currobj (ssadd (entlast) currobj))
(setq coords (list 
(list 3519.4375 818.137) 
(list 3445.415 817.787) 
(list 3445.415 817.61) 
(list 3519.4375 818.06)))
(apply 'command (append '("pline") coords '("c")))
(setq currobj (ssadd (entlast) currobj))
(setq coords (list 
(list 3519.4375 817.917) 
(list 3445.415 817.467) 
(list 3445.415 817.29) 
(list 3519.4375 817.84)))
(apply 'command (append '("pline") coords '("c")))
(setq currobj (ssadd (entlast) currobj))
(setq coords (list 
(list 3519.4375 817.697) 
(list 3445.415 817.147) 
(list 3445.415 816.97) 
(list 3519.4375 817.62)))
(apply 'command (append '("pline") coords '("c")))
(setq currobj (ssadd (entlast) currobj))
(setq coords (list 
(list 3519.4375 817.477) 
(list 3445.415 816.827) 
(list 3445.415 816.65) 
(list 3519.4375 817.4)))
(apply 'command (append '("pline") coords '("c")))
(setq currobj (ssadd (entlast) currobj))
(command "_layer" "set" "nitride" "")
(command "_layer" "set" "text" "")
(command "_circle" "3519.0625,806.257" "0.075")
(command "_circle" "3519.0625,806.557" "0.075")
(command "_circle" "3519.0625,806.857" "0.075")
(command "_circle" "3519.0625,807.157" "0.075")
(command "_circle" "3519.0625,807.457" "0.075")
(command "_circle" "3518.7625,806.257" "0.075")
(command "_circle" "3518.7625,806.557" "0.075")
(command "_circle" "3518.7625,806.857" "0.075")
(command "_circle" "3518.7625,807.157" "0.075")
(command "_circle" "3518.7625,807.457" "0.075")
(command "_circle" "3518.4625,806.257" "0.075")
(command "_circle" "3518.4625,806.557" "0.075")
(command "_circle" "3518.4625,806.857" "0.075")
(command "_circle" "3518.4625,807.157" "0.075")
(command "_circle" "3518.4625,807.457" "0.075")
(command "_circle" "3518.1625,806.257" "0.075")
(command "_circle" "3518.1625,806.557" "0.075")
(command "_circle" "3518.1625,806.857" "0.075")
(command "_circle" "3518.1625,807.157" "0.075")
(command "_circle" "3518.1625,807.457" "0.075")
(command "_circle" "3517.8625,806.257" "0.075")
(command "_circle" "3517.8625,806.557" "0.075")
(command "_circle" "3517.8625,806.857" "0.075")
(command "_circle" "3517.8625,807.157" "0.075")
(command "_circle" "3517.8625,807.457" "0.075")
(command "_layer" "set" "nitride" "")
(setq coords (list 
(list 3520.2625 831.7) 
(list 3520.2625 836.7) 
(list 3519.7375 836.7) 
(list 3519.7375 831.7)))
(apply 'command (append '("pline") coords '("c")))
(setq currobj (ssadd (entlast) currobj))
(command "_layer" "set" "prebias" "")
(command "_rectangle" "3519.7375,831.7" "3520.2625,836.7")
(setq currobj (ssadd (entlast) currobj))
(command "_layer" "set" "nitride" "")
(setq cooledsinglenanobeam11 currobj)
(setq currobj nil)
(setq currobj (ssadd))
; DRAWING PHOTONIC CRYSTAL
(command "_layer" "set" "negYjunc" "")
(setq coords (list 
(list 3520.135 866.7) 
(list 3520 851.7) 
(list 3520 866.7)))
(apply 'command (append '("pline") coords '("c")))
(setq currobj (ssadd (entlast) currobj))
(setq coords (list 
(list 3520.2625 836.7) 
(list 3520.415 866.7) 
(list 3521.106 866.7) 
(list 3521.106 836.7)))
(apply 'command (append '("pline") coords '("c")))
(setq currobj (ssadd (entlast) currobj))
(setq coords (list 
(list 3519.865 866.7) 
(list 3520 851.7) 
(list 3520 866.7)))
(apply 'command (append '("pline") coords '("c")))
(setq currobj (ssadd (entlast) currobj))
(setq coords (list 
(list 3519.7375 836.7) 
(list 3519.585 866.7) 
(list 3518.894 866.7) 
(list 3518.894 836.7)))
(apply 'command (append '("pline") coords '("c")))
(setq currobj (ssadd (entlast) currobj))
(command "_layer" "set" "nitride" "")
(setq yjunction11 currobj)
(setq currobj nil)
(setq currobj (ssadd))
(setq tap11 nil)
(setq tap11 (ssadd))
(command "_layer" "set" "phc" "")
(setq coords (list 
(list 3520 866.7) 
(list 3520.135 866.7) 
(list 3520.135 866.7103) 
(list 3520.135 866.7206) 
(list 3520.135 866.7308) 
(list 3520.135 866.7411) 
(list 3520.135 866.7514) 
(list 3520.135 866.7617) 
(list 3520.135 866.7719) 
(list 3520.135 866.7822) 
(list 3520.135 866.7925) 
(list 3520.135 866.8028) 
(list 3520.135 866.8131) 
(list 3520.135 866.8233) 
(list 3520.135 866.8336) 
(list 3520.135 866.8439) 
(list 3520.135 866.8542) 
(list 3520.135 866.8644) 
(list 3520.135 866.8747) 
(list 3520.135 866.885) 
(list 3520.135 866.8953) 
(list 3520.135 866.9056) 
(list 3520.135 866.9158) 
(list 3520.135 866.9261) 
(list 3520.135 866.9364) 
(list 3520.135 866.9467) 
(list 3520.135 866.9569) 
(list 3520.135 866.9672) 
(list 3520.135 866.9775) 
(list 3520.135 866.9878) 
(list 3520.135 866.9981) 
(list 3520.135 867.0083) 
(list 3520.135 867.0186) 
(list 3520.135 867.0289) 
(list 3520.135 867.0392) 
(list 3520.135 867.0494) 
(list 3520.135 867.0597) 
(list 3520.135 867.07) 
(list 3520 867.07)))
(apply 'command (append '("pline") coords '("c")))
(setq tap11 (ssadd (entlast) tap11))
(command "_mirror" (entlast) "" "3520,900" "3520,901" "No")
(setq tap11 (ssadd (entlast) tap11))
(setq coords (list 
(list 3520.4242 866.7) 
(list 3520.415 866.7) 
(list 3520.4153 866.7103) 
(list 3520.4155 866.7206) 
(list 3520.4157 866.7308) 
(list 3520.4158 866.7411) 
(list 3520.4158 866.7514) 
(list 3520.4158 866.7617) 
(list 3520.4157 866.7719) 
(list 3520.4154 866.7822) 
(list 3520.4151 866.7925) 
(list 3520.4147 866.8028) 
(list 3520.4142 866.8131) 
(list 3520.4137 866.8233) 
(list 3520.4131 866.8336) 
(list 3520.4125 866.8439) 
(list 3520.412 866.8542) 
(list 3520.4115 866.8644) 
(list 3520.4111 866.8747) 
(list 3520.4108 866.885) 
(list 3520.4106 866.8953) 
(list 3520.4106 866.9056) 
(list 3520.4108 866.9158) 
(list 3520.4111 866.9261) 
(list 3520.4116 866.9364) 
(list 3520.4123 866.9467) 
(list 3520.4132 866.9569) 
(list 3520.4142 866.9672) 
(list 3520.4153 866.9775) 
(list 3520.4165 866.9878) 
(list 3520.4177 866.9981) 
(list 3520.419 867.0083) 
(list 3520.4202 867.0186) 
(list 3520.4213 867.0289) 
(list 3520.4224 867.0392) 
(list 3520.4232 867.0494) 
(list 3520.4238 867.0597) 
(list 3520.4242 867.07) 
(list 3520.4242 867.07)))
(apply 'command (append '("pline") coords '("c")))
(setq tap11 (ssadd (entlast) tap11))
(command "_mirror" (entlast) "" "3520,900" "3520,901" "No")
(setq tap11 (ssadd (entlast) tap11))
(setq coords (list 
(list 3521.106 866.7) 
(list 3520.4242 866.7) 
(list 3520.4242 866.7103) 
(list 3520.4242 866.7206) 
(list 3520.4242 866.7308) 
(list 3520.4242 866.7411) 
(list 3520.4242 866.7514) 
(list 3520.4242 866.7617) 
(list 3520.4242 866.7719) 
(list 3520.4242 866.7822) 
(list 3520.4242 866.7925) 
(list 3520.4242 866.8028) 
(list 3520.4242 866.8131) 
(list 3520.4242 866.8233) 
(list 3520.4242 866.8336) 
(list 3520.4242 866.8439) 
(list 3520.4242 866.8542) 
(list 3520.4242 866.8644) 
(list 3520.4242 866.8747) 
(list 3520.4242 866.885) 
(list 3520.4242 866.8953) 
(list 3520.4242 866.9056) 
(list 3520.4242 866.9158) 
(list 3520.4242 866.9261) 
(list 3520.4242 866.9364) 
(list 3520.4242 866.9467) 
(list 3520.4242 866.9569) 
(list 3520.4242 866.9672) 
(list 3520.4242 866.9775) 
(list 3520.4242 866.9878) 
(list 3520.4242 866.9981) 
(list 3520.4242 867.0083) 
(list 3520.4242 867.0186) 
(list 3520.4242 867.0289) 
(list 3520.4242 867.0392) 
(list 3520.4242 867.0494) 
(list 3520.4242 867.0597) 
(list 3520.4242 867.07) 
(list 3521.106 867.07)))
(apply 'command (append '("pline") coords '("c")))
(setq tap11 (ssadd (entlast) tap11))
(command "_mirror" (entlast) "" "3520,900" "3520,901" "No")
(setq tap11 (ssadd (entlast) tap11))
(setq coords (list 
(list 3520 867.07) 
(list 3520.135 867.07) 
(list 3520.135 867.0803) 
(list 3520.135 867.0906) 
(list 3520.135 867.1008) 
(list 3520.135 867.1111) 
(list 3520.135 867.1214) 
(list 3520.135 867.1317) 
(list 3520.135 867.1419) 
(list 3520.135 867.1522) 
(list 3520.135 867.1625) 
(list 3520.135 867.1728) 
(list 3520.135 867.1831) 
(list 3520.135 867.1933) 
(list 3520.135 867.2036) 
(list 3520.135 867.2139) 
(list 3520.135 867.2242) 
(list 3520.135 867.2344) 
(list 3520.135 867.2447) 
(list 3520.135 867.255) 
(list 3520.135 867.2653) 
(list 3520.135 867.2756) 
(list 3520.135 867.2858) 
(list 3520.135 867.2961) 
(list 3520.135 867.3064) 
(list 3520.135 867.3167) 
(list 3520.135 867.3269) 
(list 3520.135 867.3372) 
(list 3520.135 867.3475) 
(list 3520.135 867.3578) 
(list 3520.135 867.3681) 
(list 3520.135 867.3783) 
(list 3520.135 867.3886) 
(list 3520.135 867.3989) 
(list 3520.135 867.4092) 
(list 3520.135 867.4194) 
(list 3520.135 867.4297) 
(list 3520.135 867.44) 
(list 3520 867.44)))
(apply 'command (append '("pline") coords '("c")))
(setq tap11 (ssadd (entlast) tap11))
(command "_mirror" (entlast) "" "3520,900" "3520,901" "No")
(setq tap11 (ssadd (entlast) tap11))
(setq coords (list 
(list 3520.4334 867.07) 
(list 3520.4242 867.07) 
(list 3520.4243 867.0803) 
(list 3520.4242 867.0906) 
(list 3520.4237 867.1008) 
(list 3520.4229 867.1111) 
(list 3520.4219 867.1214) 
(list 3520.4206 867.1317) 
(list 3520.4191 867.1419) 
(list 3520.4174 867.1522) 
(list 3520.4155 867.1625) 
(list 3520.4136 867.1728) 
(list 3520.4116 867.1831) 
(list 3520.4097 867.1933) 
(list 3520.4078 867.2036) 
(list 3520.4062 867.2139) 
(list 3520.4048 867.2242) 
(list 3520.4036 867.2344) 
(list 3520.4028 867.2447) 
(list 3520.4024 867.255) 
(list 3520.4024 867.2653) 
(list 3520.4028 867.2756) 
(list 3520.4036 867.2858) 
(list 3520.4048 867.2961) 
(list 3520.4064 867.3064) 
(list 3520.4083 867.3167) 
(list 3520.4106 867.3269) 
(list 3520.4131 867.3372) 
(list 3520.4157 867.3475) 
(list 3520.4184 867.3578) 
(list 3520.4212 867.3681) 
(list 3520.4238 867.3783) 
(list 3520.4263 867.3886) 
(list 3520.4285 867.3989) 
(list 3520.4304 867.4092) 
(list 3520.4319 867.4194) 
(list 3520.4329 867.4297) 
(list 3520.4334 867.44) 
(list 3520.4334 867.44)))
(apply 'command (append '("pline") coords '("c")))
(setq tap11 (ssadd (entlast) tap11))
(command "_mirror" (entlast) "" "3520,900" "3520,901" "No")
(setq tap11 (ssadd (entlast) tap11))
(setq coords (list 
(list 3521.106 867.07) 
(list 3520.4334 867.07) 
(list 3520.4334 867.0803) 
(list 3520.4334 867.0906) 
(list 3520.4334 867.1008) 
(list 3520.4334 867.1111) 
(list 3520.4334 867.1214) 
(list 3520.4334 867.1317) 
(list 3520.4334 867.1419) 
(list 3520.4334 867.1522) 
(list 3520.4334 867.1625) 
(list 3520.4334 867.1728) 
(list 3520.4334 867.1831) 
(list 3520.4334 867.1933) 
(list 3520.4334 867.2036) 
(list 3520.4334 867.2139) 
(list 3520.4334 867.2242) 
(list 3520.4334 867.2344) 
(list 3520.4334 867.2447) 
(list 3520.4334 867.255) 
(list 3520.4334 867.2653) 
(list 3520.4334 867.2756) 
(list 3520.4334 867.2858) 
(list 3520.4334 867.2961) 
(list 3520.4334 867.3064) 
(list 3520.4334 867.3167) 
(list 3520.4334 867.3269) 
(list 3520.4334 867.3372) 
(list 3520.4334 867.3475) 
(list 3520.4334 867.3578) 
(list 3520.4334 867.3681) 
(list 3520.4334 867.3783) 
(list 3520.4334 867.3886) 
(list 3520.4334 867.3989) 
(list 3520.4334 867.4092) 
(list 3520.4334 867.4194) 
(list 3520.4334 867.4297) 
(list 3520.4334 867.44) 
(list 3521.106 867.44)))
(apply 'command (append '("pline") coords '("c")))
(setq tap11 (ssadd (entlast) tap11))
(command "_mirror" (entlast) "" "3520,900" "3520,901" "No")
(setq tap11 (ssadd (entlast) tap11))
(setq coords (list 
(list 3520 867.44) 
(list 3520.135 867.44) 
(list 3520.135 867.4503) 
(list 3520.135 867.4606) 
(list 3520.135 867.4708) 
(list 3520.135 867.4811) 
(list 3520.135 867.4914) 
(list 3520.135 867.5017) 
(list 3520.135 867.5119) 
(list 3520.135 867.5222) 
(list 3520.135 867.5325) 
(list 3520.135 867.5428) 
(list 3520.135 867.5531) 
(list 3520.135 867.5633) 
(list 3520.135 867.5736) 
(list 3520.135 867.5839) 
(list 3520.135 867.5942) 
(list 3520.135 867.6044) 
(list 3520.135 867.6147) 
(list 3520.135 867.625) 
(list 3520.135 867.6353) 
(list 3520.135 867.6456) 
(list 3520.135 867.6558) 
(list 3520.135 867.6661) 
(list 3520.135 867.6764) 
(list 3520.135 867.6867) 
(list 3520.135 867.6969) 
(list 3520.135 867.7072) 
(list 3520.135 867.7175) 
(list 3520.135 867.7278) 
(list 3520.135 867.7381) 
(list 3520.135 867.7483) 
(list 3520.135 867.7586) 
(list 3520.135 867.7689) 
(list 3520.135 867.7792) 
(list 3520.135 867.7894) 
(list 3520.135 867.7997) 
(list 3520.135 867.81) 
(list 3520 867.81)))
(apply 'command (append '("pline") coords '("c")))
(setq tap11 (ssadd (entlast) tap11))
(command "_mirror" (entlast) "" "3520,900" "3520,901" "No")
(setq tap11 (ssadd (entlast) tap11))
(setq coords (list 
(list 3520.4426 867.44) 
(list 3520.4334 867.44) 
(list 3520.4334 867.4503) 
(list 3520.4328 867.4606) 
(list 3520.4317 867.4708) 
(list 3520.4301 867.4811) 
(list 3520.428 867.4914) 
(list 3520.4254 867.5017) 
(list 3520.4225 867.5119) 
(list 3520.4193 867.5222) 
(list 3520.4159 867.5325) 
(list 3520.4124 867.5428) 
(list 3520.409 867.5531) 
(list 3520.4057 867.5633) 
(list 3520.4026 867.5736) 
(list 3520.3999 867.5839) 
(list 3520.3975 867.5942) 
(list 3520.3958 867.6044) 
(list 3520.3946 867.6147) 
(list 3520.394 867.625) 
(list 3520.3941 867.6353) 
(list 3520.3949 867.6456) 
(list 3520.3963 867.6558) 
(list 3520.3984 867.6661) 
(list 3520.4011 867.6764) 
(list 3520.4043 867.6867) 
(list 3520.408 867.6969) 
(list 3520.4119 867.7072) 
(list 3520.4161 867.7175) 
(list 3520.4204 867.7278) 
(list 3520.4246 867.7381) 
(list 3520.4286 867.7483) 
(list 3520.4323 867.7586) 
(list 3520.4356 867.7689) 
(list 3520.4384 867.7792) 
(list 3520.4405 867.7894) 
(list 3520.4419 867.7997) 
(list 3520.4426 867.81) 
(list 3520.4426 867.81)))
(apply 'command (append '("pline") coords '("c")))
(setq tap11 (ssadd (entlast) tap11))
(command "_mirror" (entlast) "" "3520,900" "3520,901" "No")
(setq tap11 (ssadd (entlast) tap11))
(setq coords (list 
(list 3521.106 867.44) 
(list 3520.4426 867.44) 
(list 3520.4426 867.4503) 
(list 3520.4426 867.4606) 
(list 3520.4426 867.4708) 
(list 3520.4426 867.4811) 
(list 3520.4426 867.4914) 
(list 3520.4426 867.5017) 
(list 3520.4426 867.5119) 
(list 3520.4426 867.5222) 
(list 3520.4426 867.5325) 
(list 3520.4426 867.5428) 
(list 3520.4426 867.5531) 
(list 3520.4426 867.5633) 
(list 3520.4426 867.5736) 
(list 3520.4426 867.5839) 
(list 3520.4426 867.5942) 
(list 3520.4426 867.6044) 
(list 3520.4426 867.6147) 
(list 3520.4426 867.625) 
(list 3520.4426 867.6353) 
(list 3520.4426 867.6456) 
(list 3520.4426 867.6558) 
(list 3520.4426 867.6661) 
(list 3520.4426 867.6764) 
(list 3520.4426 867.6867) 
(list 3520.4426 867.6969) 
(list 3520.4426 867.7072) 
(list 3520.4426 867.7175) 
(list 3520.4426 867.7278) 
(list 3520.4426 867.7381) 
(list 3520.4426 867.7483) 
(list 3520.4426 867.7586) 
(list 3520.4426 867.7689) 
(list 3520.4426 867.7792) 
(list 3520.4426 867.7894) 
(list 3520.4426 867.7997) 
(list 3520.4426 867.81) 
(list 3521.106 867.81)))
(apply 'command (append '("pline") coords '("c")))
(setq tap11 (ssadd (entlast) tap11))
(command "_mirror" (entlast) "" "3520,900" "3520,901" "No")
(setq tap11 (ssadd (entlast) tap11))
(setq coords (list 
(list 3520 867.81) 
(list 3520.135 867.81) 
(list 3520.135 867.8203) 
(list 3520.135 867.8306) 
(list 3520.135 867.8408) 
(list 3520.135 867.8511) 
(list 3520.135 867.8614) 
(list 3520.135 867.8717) 
(list 3520.135 867.8819) 
(list 3520.135 867.8922) 
(list 3520.135 867.9025) 
(list 3520.135 867.9128) 
(list 3520.135 867.9231) 
(list 3520.135 867.9333) 
(list 3520.135 867.9436) 
(list 3520.135 867.9539) 
(list 3520.135 867.9642) 
(list 3520.135 867.9744) 
(list 3520.135 867.9847) 
(list 3520.135 867.995) 
(list 3520.135 868.0053) 
(list 3520.135 868.0156) 
(list 3520.135 868.0258) 
(list 3520.135 868.0361) 
(list 3520.135 868.0464) 
(list 3520.135 868.0567) 
(list 3520.135 868.0669) 
(list 3520.135 868.0772) 
(list 3520.135 868.0875) 
(list 3520.135 868.0978) 
(list 3520.135 868.1081) 
(list 3520.135 868.1183) 
(list 3520.135 868.1286) 
(list 3520.135 868.1389) 
(list 3520.135 868.1492) 
(list 3520.135 868.1594) 
(list 3520.135 868.1697) 
(list 3520.135 868.18) 
(list 3520 868.18)))
(apply 'command (append '("pline") coords '("c")))
(setq tap11 (ssadd (entlast) tap11))
(command "_mirror" (entlast) "" "3520,900" "3520,901" "No")
(setq tap11 (ssadd (entlast) tap11))
(setq coords (list 
(list 3520.4518 867.81) 
(list 3520.4426 867.81) 
(list 3520.4425 867.8203) 
(list 3520.4415 867.8306) 
(list 3520.4397 867.8408) 
(list 3520.4372 867.8511) 
(list 3520.434 867.8614) 
(list 3520.4302 867.8717) 
(list 3520.4259 867.8819) 
(list 3520.4212 867.8922) 
(list 3520.4163 867.9025) 
(list 3520.4113 867.9128) 
(list 3520.4064 867.9231) 
(list 3520.4017 867.9333) 
(list 3520.3973 867.9436) 
(list 3520.3935 867.9539) 
(list 3520.3903 867.9642) 
(list 3520.3879 867.9744) 
(list 3520.3863 867.9847) 
(list 3520.3856 867.995) 
(list 3520.3858 868.0053) 
(list 3520.387 868.0156) 
(list 3520.3891 868.0258) 
(list 3520.3921 868.0361) 
(list 3520.3959 868.0464) 
(list 3520.4003 868.0567) 
(list 3520.4054 868.0669) 
(list 3520.4108 868.0772) 
(list 3520.4165 868.0875) 
(list 3520.4223 868.0978) 
(list 3520.428 868.1081) 
(list 3520.4334 868.1183) 
(list 3520.4384 868.1286) 
(list 3520.4428 868.1389) 
(list 3520.4464 868.1492) 
(list 3520.4492 868.1594) 
(list 3520.451 868.1697) 
(list 3520.4518 868.18) 
(list 3520.4518 868.18)))
(apply 'command (append '("pline") coords '("c")))
(setq tap11 (ssadd (entlast) tap11))
(command "_mirror" (entlast) "" "3520,900" "3520,901" "No")
(setq tap11 (ssadd (entlast) tap11))
(setq coords (list 
(list 3521.106 867.81) 
(list 3520.4518 867.81) 
(list 3520.4518 867.8203) 
(list 3520.4518 867.8306) 
(list 3520.4518 867.8408) 
(list 3520.4518 867.8511) 
(list 3520.4518 867.8614) 
(list 3520.4518 867.8717) 
(list 3520.4518 867.8819) 
(list 3520.4518 867.8922) 
(list 3520.4518 867.9025) 
(list 3520.4518 867.9128) 
(list 3520.4518 867.9231) 
(list 3520.4518 867.9333) 
(list 3520.4518 867.9436) 
(list 3520.4518 867.9539) 
(list 3520.4518 867.9642) 
(list 3520.4518 867.9744) 
(list 3520.4518 867.9847) 
(list 3520.4518 867.995) 
(list 3520.4518 868.0053) 
(list 3520.4518 868.0156) 
(list 3520.4518 868.0258) 
(list 3520.4518 868.0361) 
(list 3520.4518 868.0464) 
(list 3520.4518 868.0567) 
(list 3520.4518 868.0669) 
(list 3520.4518 868.0772) 
(list 3520.4518 868.0875) 
(list 3520.4518 868.0978) 
(list 3520.4518 868.1081) 
(list 3520.4518 868.1183) 
(list 3520.4518 868.1286) 
(list 3520.4518 868.1389) 
(list 3520.4518 868.1492) 
(list 3520.4518 868.1594) 
(list 3520.4518 868.1697) 
(list 3520.4518 868.18) 
(list 3521.106 868.18)))
(apply 'command (append '("pline") coords '("c")))
(setq tap11 (ssadd (entlast) tap11))
(command "_mirror" (entlast) "" "3520,900" "3520,901" "No")
(setq tap11 (ssadd (entlast) tap11))
(setq coords (list 
(list 3520 868.18) 
(list 3520.135 868.18) 
(list 3520.135 868.1903) 
(list 3520.135 868.2006) 
(list 3520.135 868.2108) 
(list 3520.135 868.2211) 
(list 3520.135 868.2314) 
(list 3520.135 868.2417) 
(list 3520.135 868.2519) 
(list 3520.135 868.2622) 
(list 3520.135 868.2725) 
(list 3520.135 868.2828) 
(list 3520.135 868.2931) 
(list 3520.135 868.3033) 
(list 3520.135 868.3136) 
(list 3520.135 868.3239) 
(list 3520.135 868.3342) 
(list 3520.135 868.3444) 
(list 3520.135 868.3547) 
(list 3520.135 868.365) 
(list 3520.135 868.3753) 
(list 3520.135 868.3856) 
(list 3520.135 868.3958) 
(list 3520.135 868.4061) 
(list 3520.135 868.4164) 
(list 3520.135 868.4267) 
(list 3520.135 868.4369) 
(list 3520.135 868.4472) 
(list 3520.135 868.4575) 
(list 3520.135 868.4678) 
(list 3520.135 868.4781) 
(list 3520.135 868.4883) 
(list 3520.135 868.4986) 
(list 3520.135 868.5089) 
(list 3520.135 868.5192) 
(list 3520.135 868.5294) 
(list 3520.135 868.5397) 
(list 3520.135 868.55) 
(list 3520 868.55)))
(apply 'command (append '("pline") coords '("c")))
(setq tap11 (ssadd (entlast) tap11))
(command "_mirror" (entlast) "" "3520,900" "3520,901" "No")
(setq tap11 (ssadd (entlast) tap11))
(setq coords (list 
(list 3520.461 868.18) 
(list 3520.4518 868.18) 
(list 3520.4515 868.1903) 
(list 3520.4502 868.2006) 
(list 3520.4478 868.2108) 
(list 3520.4444 868.2211) 
(list 3520.4401 868.2314) 
(list 3520.435 868.2417) 
(list 3520.4293 868.2519) 
(list 3520.4231 868.2622) 
(list 3520.4167 868.2725) 
(list 3520.4102 868.2828) 
(list 3520.4038 868.2931) 
(list 3520.3977 868.3033) 
(list 3520.3921 868.3136) 
(list 3520.3872 868.3239) 
(list 3520.3831 868.3342) 
(list 3520.38 868.3444) 
(list 3520.378 868.3547) 
(list 3520.3772 868.365) 
(list 3520.3776 868.3753) 
(list 3520.3792 868.3856) 
(list 3520.3819 868.3958) 
(list 3520.3858 868.4061) 
(list 3520.3906 868.4164) 
(list 3520.3963 868.4267) 
(list 3520.4027 868.4369) 
(list 3520.4097 868.4472) 
(list 3520.4169 868.4575) 
(list 3520.4242 868.4678) 
(list 3520.4314 868.4781) 
(list 3520.4382 868.4883) 
(list 3520.4444 868.4986) 
(list 3520.4499 868.5089) 
(list 3520.4544 868.5192) 
(list 3520.4579 868.5294) 
(list 3520.4601 868.5397) 
(list 3520.461 868.55) 
(list 3520.461 868.55)))
(apply 'command (append '("pline") coords '("c")))
(setq tap11 (ssadd (entlast) tap11))
(command "_mirror" (entlast) "" "3520,900" "3520,901" "No")
(setq tap11 (ssadd (entlast) tap11))
(setq coords (list 
(list 3521.106 868.18) 
(list 3520.461 868.18) 
(list 3520.461 868.1903) 
(list 3520.461 868.2006) 
(list 3520.461 868.2108) 
(list 3520.461 868.2211) 
(list 3520.461 868.2314) 
(list 3520.461 868.2417) 
(list 3520.461 868.2519) 
(list 3520.461 868.2622) 
(list 3520.461 868.2725) 
(list 3520.461 868.2828) 
(list 3520.461 868.2931) 
(list 3520.461 868.3033) 
(list 3520.461 868.3136) 
(list 3520.461 868.3239) 
(list 3520.461 868.3342) 
(list 3520.461 868.3444) 
(list 3520.461 868.3547) 
(list 3520.461 868.365) 
(list 3520.461 868.3753) 
(list 3520.461 868.3856) 
(list 3520.461 868.3958) 
(list 3520.461 868.4061) 
(list 3520.461 868.4164) 
(list 3520.461 868.4267) 
(list 3520.461 868.4369) 
(list 3520.461 868.4472) 
(list 3520.461 868.4575) 
(list 3520.461 868.4678) 
(list 3520.461 868.4781) 
(list 3520.461 868.4883) 
(list 3520.461 868.4986) 
(list 3520.461 868.5089) 
(list 3520.461 868.5192) 
(list 3520.461 868.5294) 
(list 3520.461 868.5397) 
(list 3520.461 868.55) 
(list 3521.106 868.55)))
(apply 'command (append '("pline") coords '("c")))
(setq tap11 (ssadd (entlast) tap11))
(command "_mirror" (entlast) "" "3520,900" "3520,901" "No")
(setq tap11 (ssadd (entlast) tap11))
(setq coords (list 
(list 3520 868.55) 
(list 3520.135 868.55) 
(list 3520.135 868.5603) 
(list 3520.135 868.5706) 
(list 3520.135 868.5808) 
(list 3520.135 868.5911) 
(list 3520.135 868.6014) 
(list 3520.135 868.6117) 
(list 3520.135 868.6219) 
(list 3520.135 868.6322) 
(list 3520.135 868.6425) 
(list 3520.135 868.6528) 
(list 3520.135 868.6631) 
(list 3520.135 868.6733) 
(list 3520.135 868.6836) 
(list 3520.135 868.6939) 
(list 3520.135 868.7042) 
(list 3520.135 868.7144) 
(list 3520.135 868.7247) 
(list 3520.135 868.735) 
(list 3520.135 868.7453) 
(list 3520.135 868.7556) 
(list 3520.135 868.7658) 
(list 3520.135 868.7761) 
(list 3520.135 868.7864) 
(list 3520.135 868.7967) 
(list 3520.135 868.8069) 
(list 3520.135 868.8172) 
(list 3520.135 868.8275) 
(list 3520.135 868.8378) 
(list 3520.135 868.8481) 
(list 3520.135 868.8583) 
(list 3520.135 868.8686) 
(list 3520.135 868.8789) 
(list 3520.135 868.8892) 
(list 3520.135 868.8994) 
(list 3520.135 868.9097) 
(list 3520.135 868.92) 
(list 3520 868.92)))
(apply 'command (append '("pline") coords '("c")))
(setq tap11 (ssadd (entlast) tap11))
(command "_mirror" (entlast) "" "3520,900" "3520,901" "No")
(setq tap11 (ssadd (entlast) tap11))
(setq coords (list 
(list 3520.4702 868.55) 
(list 3520.461 868.55) 
(list 3520.4606 868.5603) 
(list 3520.4588 868.5706) 
(list 3520.4558 868.5808) 
(list 3520.4515 868.5911) 
(list 3520.4461 868.6014) 
(list 3520.4398 868.6117) 
(list 3520.4327 868.6219) 
(list 3520.4251 868.6322) 
(list 3520.4171 868.6425) 
(list 3520.409 868.6528) 
(list 3520.4012 868.6631) 
(list 3520.3937 868.6733) 
(list 3520.3868 868.6836) 
(list 3520.3808 868.6939) 
(list 3520.3759 868.7042) 
(list 3520.3722 868.7144) 
(list 3520.3698 868.7247) 
(list 3520.3688 868.735) 
(list 3520.3693 868.7453) 
(list 3520.3713 868.7556) 
(list 3520.3747 868.7658) 
(list 3520.3794 868.7761) 
(list 3520.3854 868.7864) 
(list 3520.3923 868.7967) 
(list 3520.4001 868.8069) 
(list 3520.4085 868.8172) 
(list 3520.4173 868.8275) 
(list 3520.4261 868.8378) 
(list 3520.4348 868.8481) 
(list 3520.443 868.8583) 
(list 3520.4505 868.8686) 
(list 3520.4571 868.8789) 
(list 3520.4625 868.8892) 
(list 3520.4665 868.8994) 
(list 3520.4691 868.9097) 
(list 3520.4702 868.92) 
(list 3520.4702 868.92)))
(apply 'command (append '("pline") coords '("c")))
(setq tap11 (ssadd (entlast) tap11))
(command "_mirror" (entlast) "" "3520,900" "3520,901" "No")
(setq tap11 (ssadd (entlast) tap11))
(setq coords (list 
(list 3521.106 868.55) 
(list 3520.4702 868.55) 
(list 3520.4702 868.5603) 
(list 3520.4702 868.5706) 
(list 3520.4702 868.5808) 
(list 3520.4702 868.5911) 
(list 3520.4702 868.6014) 
(list 3520.4702 868.6117) 
(list 3520.4702 868.6219) 
(list 3520.4702 868.6322) 
(list 3520.4702 868.6425) 
(list 3520.4702 868.6528) 
(list 3520.4702 868.6631) 
(list 3520.4702 868.6733) 
(list 3520.4702 868.6836) 
(list 3520.4702 868.6939) 
(list 3520.4702 868.7042) 
(list 3520.4702 868.7144) 
(list 3520.4702 868.7247) 
(list 3520.4702 868.735) 
(list 3520.4702 868.7453) 
(list 3520.4702 868.7556) 
(list 3520.4702 868.7658) 
(list 3520.4702 868.7761) 
(list 3520.4702 868.7864) 
(list 3520.4702 868.7967) 
(list 3520.4702 868.8069) 
(list 3520.4702 868.8172) 
(list 3520.4702 868.8275) 
(list 3520.4702 868.8378) 
(list 3520.4702 868.8481) 
(list 3520.4702 868.8583) 
(list 3520.4702 868.8686) 
(list 3520.4702 868.8789) 
(list 3520.4702 868.8892) 
(list 3520.4702 868.8994) 
(list 3520.4702 868.9097) 
(list 3520.4702 868.92) 
(list 3521.106 868.92)))
(apply 'command (append '("pline") coords '("c")))
(setq tap11 (ssadd (entlast) tap11))
(command "_mirror" (entlast) "" "3520,900" "3520,901" "No")
(setq tap11 (ssadd (entlast) tap11))
(setq coords (list 
(list 3520 868.92) 
(list 3520.135 868.92) 
(list 3520.135 868.9303) 
(list 3520.135 868.9406) 
(list 3520.135 868.9508) 
(list 3520.135 868.9611) 
(list 3520.135 868.9714) 
(list 3520.135 868.9817) 
(list 3520.135 868.9919) 
(list 3520.135 869.0022) 
(list 3520.135 869.0125) 
(list 3520.135 869.0228) 
(list 3520.135 869.0331) 
(list 3520.135 869.0433) 
(list 3520.135 869.0536) 
(list 3520.135 869.0639) 
(list 3520.135 869.0742) 
(list 3520.135 869.0844) 
(list 3520.135 869.0947) 
(list 3520.135 869.105) 
(list 3520.135 869.1153) 
(list 3520.135 869.1256) 
(list 3520.135 869.1358) 
(list 3520.135 869.1461) 
(list 3520.135 869.1564) 
(list 3520.135 869.1667) 
(list 3520.135 869.1769) 
(list 3520.135 869.1872) 
(list 3520.135 869.1975) 
(list 3520.135 869.2078) 
(list 3520.135 869.2181) 
(list 3520.135 869.2283) 
(list 3520.135 869.2386) 
(list 3520.135 869.2489) 
(list 3520.135 869.2592) 
(list 3520.135 869.2694) 
(list 3520.135 869.2797) 
(list 3520.135 869.29) 
(list 3520 869.29)))
(apply 'command (append '("pline") coords '("c")))
(setq tap11 (ssadd (entlast) tap11))
(command "_mirror" (entlast) "" "3520,900" "3520,901" "No")
(setq tap11 (ssadd (entlast) tap11))
(setq coords (list 
(list 3520.4794 868.92) 
(list 3520.4702 868.92) 
(list 3520.4697 868.9303) 
(list 3520.4675 868.9406) 
(list 3520.4638 868.9508) 
(list 3520.4586 868.9611) 
(list 3520.4522 868.9714) 
(list 3520.4446 868.9817) 
(list 3520.4361 868.9919) 
(list 3520.427 869.0022) 
(list 3520.4175 869.0125) 
(list 3520.4079 869.0228) 
(list 3520.3985 869.0331) 
(list 3520.3897 869.0433) 
(list 3520.3816 869.0536) 
(list 3520.3745 869.0639) 
(list 3520.3687 869.0742) 
(list 3520.3643 869.0844) 
(list 3520.3615 869.0947) 
(list 3520.3604 869.105) 
(list 3520.361 869.1153) 
(list 3520.3634 869.1256) 
(list 3520.3675 869.1358) 
(list 3520.3731 869.1461) 
(list 3520.3801 869.1564) 
(list 3520.3883 869.1667) 
(list 3520.3975 869.1769) 
(list 3520.4074 869.1872) 
(list 3520.4177 869.1975) 
(list 3520.4281 869.2078) 
(list 3520.4382 869.2181) 
(list 3520.4478 869.2283) 
(list 3520.4566 869.2386) 
(list 3520.4642 869.2489) 
(list 3520.4705 869.2592) 
(list 3520.4752 869.2694) 
(list 3520.4782 869.2797) 
(list 3520.4794 869.29) 
(list 3520.4794 869.29)))
(apply 'command (append '("pline") coords '("c")))
(setq tap11 (ssadd (entlast) tap11))
(command "_mirror" (entlast) "" "3520,900" "3520,901" "No")
(setq tap11 (ssadd (entlast) tap11))
(setq coords (list 
(list 3521.106 868.92) 
(list 3520.4794 868.92) 
(list 3520.4794 868.9303) 
(list 3520.4794 868.9406) 
(list 3520.4794 868.9508) 
(list 3520.4794 868.9611) 
(list 3520.4794 868.9714) 
(list 3520.4794 868.9817) 
(list 3520.4794 868.9919) 
(list 3520.4794 869.0022) 
(list 3520.4794 869.0125) 
(list 3520.4794 869.0228) 
(list 3520.4794 869.0331) 
(list 3520.4794 869.0433) 
(list 3520.4794 869.0536) 
(list 3520.4794 869.0639) 
(list 3520.4794 869.0742) 
(list 3520.4794 869.0844) 
(list 3520.4794 869.0947) 
(list 3520.4794 869.105) 
(list 3520.4794 869.1153) 
(list 3520.4794 869.1256) 
(list 3520.4794 869.1358) 
(list 3520.4794 869.1461) 
(list 3520.4794 869.1564) 
(list 3520.4794 869.1667) 
(list 3520.4794 869.1769) 
(list 3520.4794 869.1872) 
(list 3520.4794 869.1975) 
(list 3520.4794 869.2078) 
(list 3520.4794 869.2181) 
(list 3520.4794 869.2283) 
(list 3520.4794 869.2386) 
(list 3520.4794 869.2489) 
(list 3520.4794 869.2592) 
(list 3520.4794 869.2694) 
(list 3520.4794 869.2797) 
(list 3520.4794 869.29) 
(list 3521.106 869.29)))
(apply 'command (append '("pline") coords '("c")))
(setq tap11 (ssadd (entlast) tap11))
(command "_mirror" (entlast) "" "3520,900" "3520,901" "No")
(setq tap11 (ssadd (entlast) tap11))
(setq coords (list 
(list 3520 869.29) 
(list 3520.135 869.29) 
(list 3520.135 869.3003) 
(list 3520.135 869.3106) 
(list 3520.135 869.3208) 
(list 3520.135 869.3311) 
(list 3520.135 869.3414) 
(list 3520.135 869.3517) 
(list 3520.135 869.3619) 
(list 3520.135 869.3722) 
(list 3520.135 869.3825) 
(list 3520.135 869.3928) 
(list 3520.135 869.4031) 
(list 3520.135 869.4133) 
(list 3520.135 869.4236) 
(list 3520.135 869.4339) 
(list 3520.135 869.4442) 
(list 3520.135 869.4544) 
(list 3520.135 869.4647) 
(list 3520.135 869.475) 
(list 3520.135 869.4853) 
(list 3520.135 869.4956) 
(list 3520.135 869.5058) 
(list 3520.135 869.5161) 
(list 3520.135 869.5264) 
(list 3520.135 869.5367) 
(list 3520.135 869.5469) 
(list 3520.135 869.5572) 
(list 3520.135 869.5675) 
(list 3520.135 869.5778) 
(list 3520.135 869.5881) 
(list 3520.135 869.5983) 
(list 3520.135 869.6086) 
(list 3520.135 869.6189) 
(list 3520.135 869.6292) 
(list 3520.135 869.6394) 
(list 3520.135 869.6497) 
(list 3520.135 869.66) 
(list 3520 869.66)))
(apply 'command (append '("pline") coords '("c")))
(setq tap11 (ssadd (entlast) tap11))
(command "_mirror" (entlast) "" "3520,900" "3520,901" "No")
(setq tap11 (ssadd (entlast) tap11))
(setq coords (list 
(list 3520.4886 869.29) 
(list 3520.4794 869.29) 
(list 3520.4787 869.3003) 
(list 3520.4762 869.3106) 
(list 3520.4718 869.3208) 
(list 3520.4658 869.3311) 
(list 3520.4582 869.3414) 
(list 3520.4494 869.3517) 
(list 3520.4395 869.3619) 
(list 3520.4289 869.3722) 
(list 3520.4179 869.3825) 
(list 3520.4068 869.3928) 
(list 3520.3959 869.4031) 
(list 3520.3857 869.4133) 
(list 3520.3763 869.4236) 
(list 3520.3681 869.4339) 
(list 3520.3614 869.4442) 
(list 3520.3564 869.4544) 
(list 3520.3532 869.4647) 
(list 3520.352 869.475) 
(list 3520.3528 869.4853) 
(list 3520.3555 869.4956) 
(list 3520.3602 869.5058) 
(list 3520.3667 869.5161) 
(list 3520.3748 869.5264) 
(list 3520.3843 869.5367) 
(list 3520.3949 869.5469) 
(list 3520.4063 869.5572) 
(list 3520.4181 869.5675) 
(list 3520.43 869.5778) 
(list 3520.4416 869.5881) 
(list 3520.4526 869.5983) 
(list 3520.4626 869.6086) 
(list 3520.4713 869.6189) 
(list 3520.4785 869.6292) 
(list 3520.4839 869.6394) 
(list 3520.4873 869.6497) 
(list 3520.4886 869.66) 
(list 3520.4886 869.66)))
(apply 'command (append '("pline") coords '("c")))
(setq tap11 (ssadd (entlast) tap11))
(command "_mirror" (entlast) "" "3520,900" "3520,901" "No")
(setq tap11 (ssadd (entlast) tap11))
(setq coords (list 
(list 3521.106 869.29) 
(list 3520.4886 869.29) 
(list 3520.4886 869.3003) 
(list 3520.4886 869.3106) 
(list 3520.4886 869.3208) 
(list 3520.4886 869.3311) 
(list 3520.4886 869.3414) 
(list 3520.4886 869.3517) 
(list 3520.4886 869.3619) 
(list 3520.4886 869.3722) 
(list 3520.4886 869.3825) 
(list 3520.4886 869.3928) 
(list 3520.4886 869.4031) 
(list 3520.4886 869.4133) 
(list 3520.4886 869.4236) 
(list 3520.4886 869.4339) 
(list 3520.4886 869.4442) 
(list 3520.4886 869.4544) 
(list 3520.4886 869.4647) 
(list 3520.4886 869.475) 
(list 3520.4886 869.4853) 
(list 3520.4886 869.4956) 
(list 3520.4886 869.5058) 
(list 3520.4886 869.5161) 
(list 3520.4886 869.5264) 
(list 3520.4886 869.5367) 
(list 3520.4886 869.5469) 
(list 3520.4886 869.5572) 
(list 3520.4886 869.5675) 
(list 3520.4886 869.5778) 
(list 3520.4886 869.5881) 
(list 3520.4886 869.5983) 
(list 3520.4886 869.6086) 
(list 3520.4886 869.6189) 
(list 3520.4886 869.6292) 
(list 3520.4886 869.6394) 
(list 3520.4886 869.6497) 
(list 3520.4886 869.66) 
(list 3521.106 869.66)))
(apply 'command (append '("pline") coords '("c")))
(setq tap11 (ssadd (entlast) tap11))
(command "_mirror" (entlast) "" "3520,900" "3520,901" "No")
(setq tap11 (ssadd (entlast) tap11))
(setq coords (list 
(list 3520 869.66) 
(list 3520.135 869.66) 
(list 3520.135 869.6703) 
(list 3520.135 869.6806) 
(list 3520.135 869.6908) 
(list 3520.135 869.7011) 
(list 3520.135 869.7114) 
(list 3520.135 869.7217) 
(list 3520.135 869.7319) 
(list 3520.135 869.7422) 
(list 3520.135 869.7525) 
(list 3520.135 869.7628) 
(list 3520.135 869.7731) 
(list 3520.135 869.7833) 
(list 3520.135 869.7936) 
(list 3520.135 869.8039) 
(list 3520.135 869.8142) 
(list 3520.135 869.8244) 
(list 3520.135 869.8347) 
(list 3520.135 869.845) 
(list 3520.135 869.8553) 
(list 3520.135 869.8656) 
(list 3520.135 869.8758) 
(list 3520.135 869.8861) 
(list 3520.135 869.8964) 
(list 3520.135 869.9067) 
(list 3520.135 869.9169) 
(list 3520.135 869.9272) 
(list 3520.135 869.9375) 
(list 3520.135 869.9478) 
(list 3520.135 869.9581) 
(list 3520.135 869.9683) 
(list 3520.135 869.9786) 
(list 3520.135 869.9889) 
(list 3520.135 869.9992) 
(list 3520.135 870.0094) 
(list 3520.135 870.0197) 
(list 3520.135 870.03) 
(list 3520 870.03)))
(apply 'command (append '("pline") coords '("c")))
(setq tap11 (ssadd (entlast) tap11))
(command "_mirror" (entlast) "" "3520,900" "3520,901" "No")
(setq tap11 (ssadd (entlast) tap11))
(setq coords (list 
(list 3520.4978 869.66) 
(list 3520.4886 869.66) 
(list 3520.4878 869.6703) 
(list 3520.4848 869.6806) 
(list 3520.4798 869.6908) 
(list 3520.4729 869.7011) 
(list 3520.4643 869.7114) 
(list 3520.4542 869.7217) 
(list 3520.4429 869.7319) 
(list 3520.4309 869.7422) 
(list 3520.4183 869.7525) 
(list 3520.4057 869.7628) 
(list 3520.3933 869.7731) 
(list 3520.3817 869.7833) 
(list 3520.3711 869.7936) 
(list 3520.3618 869.8039) 
(list 3520.3542 869.8142) 
(list 3520.3485 869.8244) 
(list 3520.345 869.8347) 
(list 3520.3436 869.845) 
(list 3520.3445 869.8553) 
(list 3520.3477 869.8656) 
(list 3520.353 869.8758) 
(list 3520.3604 869.8861) 
(list 3520.3696 869.8964) 
(list 3520.3803 869.9067) 
(list 3520.3923 869.9169) 
(list 3520.4052 869.9272) 
(list 3520.4185 869.9375) 
(list 3520.4319 869.9478) 
(list 3520.445 869.9581) 
(list 3520.4574 869.9683) 
(list 3520.4687 869.9786) 
(list 3520.4785 869.9889) 
(list 3520.4865 869.9992) 
(list 3520.4925 870.0094) 
(list 3520.4963 870.0197) 
(list 3520.4978 870.03) 
(list 3520.4978 870.03)))
(apply 'command (append '("pline") coords '("c")))
(setq tap11 (ssadd (entlast) tap11))
(command "_mirror" (entlast) "" "3520,900" "3520,901" "No")
(setq tap11 (ssadd (entlast) tap11))
(setq coords (list 
(list 3521.106 869.66) 
(list 3520.4978 869.66) 
(list 3520.4978 869.6703) 
(list 3520.4978 869.6806) 
(list 3520.4978 869.6908) 
(list 3520.4978 869.7011) 
(list 3520.4978 869.7114) 
(list 3520.4978 869.7217) 
(list 3520.4978 869.7319) 
(list 3520.4978 869.7422) 
(list 3520.4978 869.7525) 
(list 3520.4978 869.7628) 
(list 3520.4978 869.7731) 
(list 3520.4978 869.7833) 
(list 3520.4978 869.7936) 
(list 3520.4978 869.8039) 
(list 3520.4978 869.8142) 
(list 3520.4978 869.8244) 
(list 3520.4978 869.8347) 
(list 3520.4978 869.845) 
(list 3520.4978 869.8553) 
(list 3520.4978 869.8656) 
(list 3520.4978 869.8758) 
(list 3520.4978 869.8861) 
(list 3520.4978 869.8964) 
(list 3520.4978 869.9067) 
(list 3520.4978 869.9169) 
(list 3520.4978 869.9272) 
(list 3520.4978 869.9375) 
(list 3520.4978 869.9478) 
(list 3520.4978 869.9581) 
(list 3520.4978 869.9683) 
(list 3520.4978 869.9786) 
(list 3520.4978 869.9889) 
(list 3520.4978 869.9992) 
(list 3520.4978 870.0094) 
(list 3520.4978 870.0197) 
(list 3520.4978 870.03) 
(list 3521.106 870.03)))
(apply 'command (append '("pline") coords '("c")))
(setq tap11 (ssadd (entlast) tap11))
(command "_mirror" (entlast) "" "3520,900" "3520,901" "No")
(setq tap11 (ssadd (entlast) tap11))
(setq coords (list 
(list 3520 870.03) 
(list 3520.135 870.03) 
(list 3520.135 870.0403) 
(list 3520.135 870.0506) 
(list 3520.135 870.0608) 
(list 3520.135 870.0711) 
(list 3520.135 870.0814) 
(list 3520.135 870.0917) 
(list 3520.135 870.1019) 
(list 3520.135 870.1122) 
(list 3520.135 870.1225) 
(list 3520.135 870.1328) 
(list 3520.135 870.1431) 
(list 3520.135 870.1533) 
(list 3520.135 870.1636) 
(list 3520.135 870.1739) 
(list 3520.135 870.1842) 
(list 3520.135 870.1944) 
(list 3520.135 870.2047) 
(list 3520.135 870.215) 
(list 3520.135 870.2253) 
(list 3520.135 870.2356) 
(list 3520.135 870.2458) 
(list 3520.135 870.2561) 
(list 3520.135 870.2664) 
(list 3520.135 870.2767) 
(list 3520.135 870.2869) 
(list 3520.135 870.2972) 
(list 3520.135 870.3075) 
(list 3520.135 870.3178) 
(list 3520.135 870.3281) 
(list 3520.135 870.3383) 
(list 3520.135 870.3486) 
(list 3520.135 870.3589) 
(list 3520.135 870.3692) 
(list 3520.135 870.3794) 
(list 3520.135 870.3897) 
(list 3520.135 870.4) 
(list 3520 870.4)))
(apply 'command (append '("pline") coords '("c")))
(setq tap11 (ssadd (entlast) tap11))
(command "_mirror" (entlast) "" "3520,900" "3520,901" "No")
(setq tap11 (ssadd (entlast) tap11))
(setq coords (list 
(list 3520.507 870.03) 
(list 3520.4978 870.03) 
(list 3520.4968 870.0403) 
(list 3520.4935 870.0506) 
(list 3520.4879 870.0608) 
(list 3520.4801 870.0711) 
(list 3520.4704 870.0814) 
(list 3520.459 870.0917) 
(list 3520.4464 870.1019) 
(list 3520.4328 870.1122) 
(list 3520.4187 870.1225) 
(list 3520.4045 870.1328) 
(list 3520.3907 870.1431) 
(list 3520.3777 870.1533) 
(list 3520.3658 870.1636) 
(list 3520.3555 870.1739) 
(list 3520.347 870.1842) 
(list 3520.3407 870.1944) 
(list 3520.3367 870.2047) 
(list 3520.3352 870.215) 
(list 3520.3362 870.2253) 
(list 3520.3398 870.2356) 
(list 3520.3458 870.2458) 
(list 3520.3541 870.2561) 
(list 3520.3643 870.2664) 
(list 3520.3763 870.2767) 
(list 3520.3897 870.2869) 
(list 3520.404 870.2972) 
(list 3520.4189 870.3075) 
(list 3520.4339 870.3178) 
(list 3520.4484 870.3281) 
(list 3520.4622 870.3383) 
(list 3520.4747 870.3486) 
(list 3520.4856 870.3589) 
(list 3520.4945 870.3692) 
(list 3520.5012 870.3794) 
(list 3520.5054 870.3897) 
(list 3520.507 870.4) 
(list 3520.507 870.4)))
(apply 'command (append '("pline") coords '("c")))
(setq tap11 (ssadd (entlast) tap11))
(command "_mirror" (entlast) "" "3520,900" "3520,901" "No")
(setq tap11 (ssadd (entlast) tap11))
(setq coords (list 
(list 3521.106 870.03) 
(list 3520.507 870.03) 
(list 3520.507 870.0403) 
(list 3520.507 870.0506) 
(list 3520.507 870.0608) 
(list 3520.507 870.0711) 
(list 3520.507 870.0814) 
(list 3520.507 870.0917) 
(list 3520.507 870.1019) 
(list 3520.507 870.1122) 
(list 3520.507 870.1225) 
(list 3520.507 870.1328) 
(list 3520.507 870.1431) 
(list 3520.507 870.1533) 
(list 3520.507 870.1636) 
(list 3520.507 870.1739) 
(list 3520.507 870.1842) 
(list 3520.507 870.1944) 
(list 3520.507 870.2047) 
(list 3520.507 870.215) 
(list 3520.507 870.2253) 
(list 3520.507 870.2356) 
(list 3520.507 870.2458) 
(list 3520.507 870.2561) 
(list 3520.507 870.2664) 
(list 3520.507 870.2767) 
(list 3520.507 870.2869) 
(list 3520.507 870.2972) 
(list 3520.507 870.3075) 
(list 3520.507 870.3178) 
(list 3520.507 870.3281) 
(list 3520.507 870.3383) 
(list 3520.507 870.3486) 
(list 3520.507 870.3589) 
(list 3520.507 870.3692) 
(list 3520.507 870.3794) 
(list 3520.507 870.3897) 
(list 3520.507 870.4) 
(list 3521.106 870.4)))
(apply 'command (append '("pline") coords '("c")))
(setq tap11 (ssadd (entlast) tap11))
(command "_mirror" (entlast) "" "3520,900" "3520,901" "No")
(setq tap11 (ssadd (entlast) tap11))
(setq coords (list 
(list 3520 870.4) 
(list 3520.135 870.4) 
(list 3520.135 870.4103) 
(list 3520.135 870.4206) 
(list 3520.135 870.4308) 
(list 3520.135 870.4411) 
(list 3520.135 870.4514) 
(list 3520.135 870.4617) 
(list 3520.135 870.4719) 
(list 3520.135 870.4822) 
(list 3520.135 870.4925) 
(list 3520.135 870.5028) 
(list 3520.135 870.5131) 
(list 3520.135 870.5233) 
(list 3520.135 870.5336) 
(list 3520.135 870.5439) 
(list 3520.135 870.5542) 
(list 3520.135 870.5644) 
(list 3520.135 870.5747) 
(list 3520.135 870.585) 
(list 3520.135 870.5953) 
(list 3520.135 870.6056) 
(list 3520.135 870.6158) 
(list 3520.135 870.6261) 
(list 3520.135 870.6364) 
(list 3520.135 870.6467) 
(list 3520.135 870.6569) 
(list 3520.135 870.6672) 
(list 3520.135 870.6775) 
(list 3520.135 870.6878) 
(list 3520.135 870.6981) 
(list 3520.135 870.7083) 
(list 3520.135 870.7186) 
(list 3520.135 870.7289) 
(list 3520.135 870.7392) 
(list 3520.135 870.7494) 
(list 3520.135 870.7597) 
(list 3520.135 870.77) 
(list 3520 870.77)))
(apply 'command (append '("pline") coords '("c")))
(setq tap11 (ssadd (entlast) tap11))
(command "_mirror" (entlast) "" "3520,900" "3520,901" "No")
(setq tap11 (ssadd (entlast) tap11))
(setq coords (list 
(list 3520.5162 870.4) 
(list 3520.507 870.4) 
(list 3520.5059 870.4103) 
(list 3520.5022 870.4206) 
(list 3520.4959 870.4308) 
(list 3520.4872 870.4411) 
(list 3520.4764 870.4514) 
(list 3520.4638 870.4617) 
(list 3520.4498 870.4719) 
(list 3520.4347 870.4822) 
(list 3520.4191 870.4925) 
(list 3520.4034 870.5028) 
(list 3520.3881 870.5131) 
(list 3520.3737 870.5233) 
(list 3520.3605 870.5336) 
(list 3520.3491 870.5439) 
(list 3520.3398 870.5542) 
(list 3520.3328 870.5644) 
(list 3520.3284 870.5747) 
(list 3520.3268 870.585) 
(list 3520.328 870.5953) 
(list 3520.3319 870.6056) 
(list 3520.3386 870.6158) 
(list 3520.3477 870.6261) 
(list 3520.3591 870.6364) 
(list 3520.3723 870.6467) 
(list 3520.3871 870.6569) 
(list 3520.4029 870.6672) 
(list 3520.4193 870.6775) 
(list 3520.4358 870.6878) 
(list 3520.4518 870.6981) 
(list 3520.467 870.7083) 
(list 3520.4808 870.7186) 
(list 3520.4928 870.7289) 
(list 3520.5026 870.7392) 
(list 3520.5099 870.7494) 
(list 3520.5145 870.7597) 
(list 3520.5162 870.77) 
(list 3520.5162 870.77)))
(apply 'command (append '("pline") coords '("c")))
(setq tap11 (ssadd (entlast) tap11))
(command "_mirror" (entlast) "" "3520,900" "3520,901" "No")
(setq tap11 (ssadd (entlast) tap11))
(setq coords (list 
(list 3521.106 870.4) 
(list 3520.5162 870.4) 
(list 3520.5162 870.4103) 
(list 3520.5162 870.4206) 
(list 3520.5162 870.4308) 
(list 3520.5162 870.4411) 
(list 3520.5162 870.4514) 
(list 3520.5162 870.4617) 
(list 3520.5162 870.4719) 
(list 3520.5162 870.4822) 
(list 3520.5162 870.4925) 
(list 3520.5162 870.5028) 
(list 3520.5162 870.5131) 
(list 3520.5162 870.5233) 
(list 3520.5162 870.5336) 
(list 3520.5162 870.5439) 
(list 3520.5162 870.5542) 
(list 3520.5162 870.5644) 
(list 3520.5162 870.5747) 
(list 3520.5162 870.585) 
(list 3520.5162 870.5953) 
(list 3520.5162 870.6056) 
(list 3520.5162 870.6158) 
(list 3520.5162 870.6261) 
(list 3520.5162 870.6364) 
(list 3520.5162 870.6467) 
(list 3520.5162 870.6569) 
(list 3520.5162 870.6672) 
(list 3520.5162 870.6775) 
(list 3520.5162 870.6878) 
(list 3520.5162 870.6981) 
(list 3520.5162 870.7083) 
(list 3520.5162 870.7186) 
(list 3520.5162 870.7289) 
(list 3520.5162 870.7392) 
(list 3520.5162 870.7494) 
(list 3520.5162 870.7597) 
(list 3520.5162 870.77) 
(list 3521.106 870.77)))
(apply 'command (append '("pline") coords '("c")))
(setq tap11 (ssadd (entlast) tap11))
(command "_mirror" (entlast) "" "3520,900" "3520,901" "No")
(setq tap11 (ssadd (entlast) tap11))
(setq coords (list 
(list 3520 870.77) 
(list 3520.135 870.77) 
(list 3520.135 870.7803) 
(list 3520.135 870.7906) 
(list 3520.135 870.8008) 
(list 3520.135 870.8111) 
(list 3520.135 870.8214) 
(list 3520.135 870.8317) 
(list 3520.135 870.8419) 
(list 3520.135 870.8522) 
(list 3520.135 870.8625) 
(list 3520.135 870.8728) 
(list 3520.135 870.8831) 
(list 3520.135 870.8933) 
(list 3520.135 870.9036) 
(list 3520.135 870.9139) 
(list 3520.135 870.9242) 
(list 3520.135 870.9344) 
(list 3520.135 870.9447) 
(list 3520.135 870.955) 
(list 3520.135 870.9653) 
(list 3520.135 870.9756) 
(list 3520.135 870.9858) 
(list 3520.135 870.9961) 
(list 3520.135 871.0064) 
(list 3520.135 871.0167) 
(list 3520.135 871.0269) 
(list 3520.135 871.0372) 
(list 3520.135 871.0475) 
(list 3520.135 871.0578) 
(list 3520.135 871.0681) 
(list 3520.135 871.0783) 
(list 3520.135 871.0886) 
(list 3520.135 871.0989) 
(list 3520.135 871.1092) 
(list 3520.135 871.1194) 
(list 3520.135 871.1297) 
(list 3520.135 871.14) 
(list 3520 871.14)))
(apply 'command (append '("pline") coords '("c")))
(setq tap11 (ssadd (entlast) tap11))
(command "_mirror" (entlast) "" "3520,900" "3520,901" "No")
(setq tap11 (ssadd (entlast) tap11))
(setq coords (list 
(list 3520.5254 870.77) 
(list 3520.5162 870.77) 
(list 3520.515 870.7803) 
(list 3520.5108 870.7906) 
(list 3520.5039 870.8008) 
(list 3520.4943 870.8111) 
(list 3520.4825 870.8214) 
(list 3520.4686 870.8317) 
(list 3520.4532 870.8419) 
(list 3520.4366 870.8522) 
(list 3520.4195 870.8625) 
(list 3520.4023 870.8728) 
(list 3520.3855 870.8831) 
(list 3520.3697 870.8933) 
(list 3520.3553 870.9036) 
(list 3520.3428 870.9139) 
(list 3520.3326 870.9242) 
(list 3520.3249 870.9344) 
(list 3520.3202 870.9447) 
(list 3520.3184 870.955) 
(list 3520.3197 870.9653) 
(list 3520.3241 870.9756) 
(list 3520.3314 870.9858) 
(list 3520.3414 870.9961) 
(list 3520.3538 871.0064) 
(list 3520.3683 871.0167) 
(list 3520.3845 871.0269) 
(list 3520.4018 871.0372) 
(list 3520.4197 871.0475) 
(list 3520.4377 871.0578) 
(list 3520.4553 871.0681) 
(list 3520.4718 871.0783) 
(list 3520.4868 871.0886) 
(list 3520.4999 871.0989) 
(list 3520.5106 871.1092) 
(list 3520.5185 871.1194) 
(list 3520.5235 871.1297) 
(list 3520.5254 871.14) 
(list 3520.5254 871.14)))
(apply 'command (append '("pline") coords '("c")))
(setq tap11 (ssadd (entlast) tap11))
(command "_mirror" (entlast) "" "3520,900" "3520,901" "No")
(setq tap11 (ssadd (entlast) tap11))
(setq coords (list 
(list 3521.106 870.77) 
(list 3520.5254 870.77) 
(list 3520.5254 870.7803) 
(list 3520.5254 870.7906) 
(list 3520.5254 870.8008) 
(list 3520.5254 870.8111) 
(list 3520.5254 870.8214) 
(list 3520.5254 870.8317) 
(list 3520.5254 870.8419) 
(list 3520.5254 870.8522) 
(list 3520.5254 870.8625) 
(list 3520.5254 870.8728) 
(list 3520.5254 870.8831) 
(list 3520.5254 870.8933) 
(list 3520.5254 870.9036) 
(list 3520.5254 870.9139) 
(list 3520.5254 870.9242) 
(list 3520.5254 870.9344) 
(list 3520.5254 870.9447) 
(list 3520.5254 870.955) 
(list 3520.5254 870.9653) 
(list 3520.5254 870.9756) 
(list 3520.5254 870.9858) 
(list 3520.5254 870.9961) 
(list 3520.5254 871.0064) 
(list 3520.5254 871.0167) 
(list 3520.5254 871.0269) 
(list 3520.5254 871.0372) 
(list 3520.5254 871.0475) 
(list 3520.5254 871.0578) 
(list 3520.5254 871.0681) 
(list 3520.5254 871.0783) 
(list 3520.5254 871.0886) 
(list 3520.5254 871.0989) 
(list 3520.5254 871.1092) 
(list 3520.5254 871.1194) 
(list 3520.5254 871.1297) 
(list 3520.5254 871.14) 
(list 3521.106 871.14)))
(apply 'command (append '("pline") coords '("c")))
(setq tap11 (ssadd (entlast) tap11))
(command "_mirror" (entlast) "" "3520,900" "3520,901" "No")
(setq tap11 (ssadd (entlast) tap11))
(setq coords (list 
(list 3520 871.14) 
(list 3520.135 871.14) 
(list 3520.135 871.1503) 
(list 3520.135 871.1606) 
(list 3520.135 871.1708) 
(list 3520.135 871.1811) 
(list 3520.135 871.1914) 
(list 3520.135 871.2017) 
(list 3520.135 871.2119) 
(list 3520.135 871.2222) 
(list 3520.135 871.2325) 
(list 3520.135 871.2428) 
(list 3520.135 871.2531) 
(list 3520.135 871.2633) 
(list 3520.135 871.2736) 
(list 3520.135 871.2839) 
(list 3520.135 871.2942) 
(list 3520.135 871.3044) 
(list 3520.135 871.3147) 
(list 3520.135 871.325) 
(list 3520.135 871.3353) 
(list 3520.135 871.3456) 
(list 3520.135 871.3558) 
(list 3520.135 871.3661) 
(list 3520.135 871.3764) 
(list 3520.135 871.3867) 
(list 3520.135 871.3969) 
(list 3520.135 871.4072) 
(list 3520.135 871.4175) 
(list 3520.135 871.4278) 
(list 3520.135 871.4381) 
(list 3520.135 871.4483) 
(list 3520.135 871.4586) 
(list 3520.135 871.4689) 
(list 3520.135 871.4792) 
(list 3520.135 871.4894) 
(list 3520.135 871.4997) 
(list 3520.135 871.51) 
(list 3520 871.51)))
(apply 'command (append '("pline") coords '("c")))
(setq tap11 (ssadd (entlast) tap11))
(command "_mirror" (entlast) "" "3520,900" "3520,901" "No")
(setq tap11 (ssadd (entlast) tap11))
(setq coords (list 
(list 3520.5346 871.14) 
(list 3520.5254 871.14) 
(list 3520.524 871.1503) 
(list 3520.5195 871.1606) 
(list 3520.5119 871.1708) 
(list 3520.5015 871.1811) 
(list 3520.4885 871.1914) 
(list 3520.4734 871.2017) 
(list 3520.4566 871.2119) 
(list 3520.4386 871.2222) 
(list 3520.4199 871.2325) 
(list 3520.4011 871.2428) 
(list 3520.3829 871.2531) 
(list 3520.3657 871.2633) 
(list 3520.35 871.2736) 
(list 3520.3364 871.2839) 
(list 3520.3253 871.2942) 
(list 3520.3171 871.3044) 
(list 3520.3119 871.3147) 
(list 3520.31 871.325) 
(list 3520.3114 871.3353) 
(list 3520.3162 871.3456) 
(list 3520.3241 871.3558) 
(list 3520.335 871.3661) 
(list 3520.3486 871.3764) 
(list 3520.3643 871.3867) 
(list 3520.3819 871.3969) 
(list 3520.4006 871.4072) 
(list 3520.4201 871.4175) 
(list 3520.4396 871.4278) 
(list 3520.4587 871.4381) 
(list 3520.4766 871.4483) 
(list 3520.4929 871.4586) 
(list 3520.507 871.4689) 
(list 3520.5186 871.4792) 
(list 3520.5272 871.4894) 
(list 3520.5326 871.4997) 
(list 3520.5346 871.51) 
(list 3520.5346 871.51)))
(apply 'command (append '("pline") coords '("c")))
(setq tap11 (ssadd (entlast) tap11))
(command "_mirror" (entlast) "" "3520,900" "3520,901" "No")
(setq tap11 (ssadd (entlast) tap11))
(setq coords (list 
(list 3521.106 871.14) 
(list 3520.5346 871.14) 
(list 3520.5346 871.1503) 
(list 3520.5346 871.1606) 
(list 3520.5346 871.1708) 
(list 3520.5346 871.1811) 
(list 3520.5346 871.1914) 
(list 3520.5346 871.2017) 
(list 3520.5346 871.2119) 
(list 3520.5346 871.2222) 
(list 3520.5346 871.2325) 
(list 3520.5346 871.2428) 
(list 3520.5346 871.2531) 
(list 3520.5346 871.2633) 
(list 3520.5346 871.2736) 
(list 3520.5346 871.2839) 
(list 3520.5346 871.2942) 
(list 3520.5346 871.3044) 
(list 3520.5346 871.3147) 
(list 3520.5346 871.325) 
(list 3520.5346 871.3353) 
(list 3520.5346 871.3456) 
(list 3520.5346 871.3558) 
(list 3520.5346 871.3661) 
(list 3520.5346 871.3764) 
(list 3520.5346 871.3867) 
(list 3520.5346 871.3969) 
(list 3520.5346 871.4072) 
(list 3520.5346 871.4175) 
(list 3520.5346 871.4278) 
(list 3520.5346 871.4381) 
(list 3520.5346 871.4483) 
(list 3520.5346 871.4586) 
(list 3520.5346 871.4689) 
(list 3520.5346 871.4792) 
(list 3520.5346 871.4894) 
(list 3520.5346 871.4997) 
(list 3520.5346 871.51) 
(list 3521.106 871.51)))
(apply 'command (append '("pline") coords '("c")))
(setq tap11 (ssadd (entlast) tap11))
(command "_mirror" (entlast) "" "3520,900" "3520,901" "No")
(setq tap11 (ssadd (entlast) tap11))
(setq coords (list 
(list 3520 871.51) 
(list 3520.135 871.51) 
(list 3520.135 871.5203) 
(list 3520.135 871.5306) 
(list 3520.135 871.5408) 
(list 3520.135 871.5511) 
(list 3520.135 871.5614) 
(list 3520.135 871.5717) 
(list 3520.135 871.5819) 
(list 3520.135 871.5922) 
(list 3520.135 871.6025) 
(list 3520.135 871.6128) 
(list 3520.135 871.6231) 
(list 3520.135 871.6333) 
(list 3520.135 871.6436) 
(list 3520.135 871.6539) 
(list 3520.135 871.6642) 
(list 3520.135 871.6744) 
(list 3520.135 871.6847) 
(list 3520.135 871.695) 
(list 3520.135 871.7053) 
(list 3520.135 871.7156) 
(list 3520.135 871.7258) 
(list 3520.135 871.7361) 
(list 3520.135 871.7464) 
(list 3520.135 871.7567) 
(list 3520.135 871.7669) 
(list 3520.135 871.7772) 
(list 3520.135 871.7875) 
(list 3520.135 871.7978) 
(list 3520.135 871.8081) 
(list 3520.135 871.8183) 
(list 3520.135 871.8286) 
(list 3520.135 871.8389) 
(list 3520.135 871.8492) 
(list 3520.135 871.8594) 
(list 3520.135 871.8697) 
(list 3520.135 871.88) 
(list 3520 871.88)))
(apply 'command (append '("pline") coords '("c")))
(setq tap11 (ssadd (entlast) tap11))
(command "_mirror" (entlast) "" "3520,900" "3520,901" "No")
(setq tap11 (ssadd (entlast) tap11))
(setq coords (list 
(list 3520.5438 871.51) 
(list 3520.5346 871.51) 
(list 3520.5331 871.5203) 
(list 3520.5282 871.5306) 
(list 3520.5199 871.5408) 
(list 3520.5086 871.5511) 
(list 3520.4946 871.5614) 
(list 3520.4782 871.5717) 
(list 3520.46 871.5819) 
(list 3520.4405 871.5922) 
(list 3520.4203 871.6025) 
(list 3520.4 871.6128) 
(list 3520.3803 871.6231) 
(list 3520.3617 871.6333) 
(list 3520.3448 871.6436) 
(list 3520.3301 871.6539) 
(list 3520.3181 871.6642) 
(list 3520.3092 871.6744) 
(list 3520.3036 871.6847) 
(list 3520.3016 871.695) 
(list 3520.3032 871.7053) 
(list 3520.3083 871.7156) 
(list 3520.3169 871.7258) 
(list 3520.3287 871.7361) 
(list 3520.3433 871.7464) 
(list 3520.3603 871.7567) 
(list 3520.3793 871.7669) 
(list 3520.3995 871.7772) 
(list 3520.4205 871.7875) 
(list 3520.4416 871.7978) 
(list 3520.4621 871.8081) 
(list 3520.4814 871.8183) 
(list 3520.499 871.8286) 
(list 3520.5142 871.8389) 
(list 3520.5266 871.8492) 
(list 3520.5359 871.8594) 
(list 3520.5417 871.8697) 
(list 3520.5438 871.88) 
(list 3520.5438 871.88)))
(apply 'command (append '("pline") coords '("c")))
(setq tap11 (ssadd (entlast) tap11))
(command "_mirror" (entlast) "" "3520,900" "3520,901" "No")
(setq tap11 (ssadd (entlast) tap11))
(setq coords (list 
(list 3521.106 871.51) 
(list 3520.5438 871.51) 
(list 3520.5438 871.5203) 
(list 3520.5438 871.5306) 
(list 3520.5438 871.5408) 
(list 3520.5438 871.5511) 
(list 3520.5438 871.5614) 
(list 3520.5438 871.5717) 
(list 3520.5438 871.5819) 
(list 3520.5438 871.5922) 
(list 3520.5438 871.6025) 
(list 3520.5438 871.6128) 
(list 3520.5438 871.6231) 
(list 3520.5438 871.6333) 
(list 3520.5438 871.6436) 
(list 3520.5438 871.6539) 
(list 3520.5438 871.6642) 
(list 3520.5438 871.6744) 
(list 3520.5438 871.6847) 
(list 3520.5438 871.695) 
(list 3520.5438 871.7053) 
(list 3520.5438 871.7156) 
(list 3520.5438 871.7258) 
(list 3520.5438 871.7361) 
(list 3520.5438 871.7464) 
(list 3520.5438 871.7567) 
(list 3520.5438 871.7669) 
(list 3520.5438 871.7772) 
(list 3520.5438 871.7875) 
(list 3520.5438 871.7978) 
(list 3520.5438 871.8081) 
(list 3520.5438 871.8183) 
(list 3520.5438 871.8286) 
(list 3520.5438 871.8389) 
(list 3520.5438 871.8492) 
(list 3520.5438 871.8594) 
(list 3520.5438 871.8697) 
(list 3520.5438 871.88) 
(list 3521.106 871.88)))
(apply 'command (append '("pline") coords '("c")))
(setq tap11 (ssadd (entlast) tap11))
(command "_mirror" (entlast) "" "3520,900" "3520,901" "No")
(setq tap11 (ssadd (entlast) tap11))
(setq coords (list 
(list 3520 871.88) 
(list 3520.135 871.88) 
(list 3520.135 871.8903) 
(list 3520.135 871.9006) 
(list 3520.135 871.9108) 
(list 3520.135 871.9211) 
(list 3520.135 871.9314) 
(list 3520.135 871.9417) 
(list 3520.135 871.9519) 
(list 3520.135 871.9622) 
(list 3520.135 871.9725) 
(list 3520.135 871.9828) 
(list 3520.135 871.9931) 
(list 3520.135 872.0033) 
(list 3520.135 872.0136) 
(list 3520.135 872.0239) 
(list 3520.135 872.0342) 
(list 3520.135 872.0444) 
(list 3520.135 872.0547) 
(list 3520.135 872.065) 
(list 3520.135 872.0753) 
(list 3520.135 872.0856) 
(list 3520.135 872.0958) 
(list 3520.135 872.1061) 
(list 3520.135 872.1164) 
(list 3520.135 872.1267) 
(list 3520.135 872.1369) 
(list 3520.135 872.1472) 
(list 3520.135 872.1575) 
(list 3520.135 872.1678) 
(list 3520.135 872.1781) 
(list 3520.135 872.1883) 
(list 3520.135 872.1986) 
(list 3520.135 872.2089) 
(list 3520.135 872.2192) 
(list 3520.135 872.2294) 
(list 3520.135 872.2397) 
(list 3520.135 872.25) 
(list 3520 872.25)))
(apply 'command (append '("pline") coords '("c")))
(setq tap11 (ssadd (entlast) tap11))
(command "_mirror" (entlast) "" "3520,900" "3520,901" "No")
(setq tap11 (ssadd (entlast) tap11))
(setq coords (list 
(list 3520.553 871.88) 
(list 3520.5438 871.88) 
(list 3520.5422 871.8903) 
(list 3520.5369 871.9006) 
(list 3520.528 871.9108) 
(list 3520.5158 871.9211) 
(list 3520.5006 871.9314) 
(list 3520.483 871.9417) 
(list 3520.4634 871.9519) 
(list 3520.4424 871.9622) 
(list 3520.4207 871.9725) 
(list 3520.3989 871.9828) 
(list 3520.3777 871.9931) 
(list 3520.3577 872.0033) 
(list 3520.3395 872.0136) 
(list 3520.3238 872.0239) 
(list 3520.3109 872.0342) 
(list 3520.3013 872.0444) 
(list 3520.2954 872.0547) 
(list 3520.2932 872.065) 
(list 3520.2949 872.0753) 
(list 3520.3005 872.0856) 
(list 3520.3097 872.0958) 
(list 3520.3223 872.1061) 
(list 3520.338 872.1164) 
(list 3520.3563 872.1267) 
(list 3520.3767 872.1369) 
(list 3520.3984 872.1472) 
(list 3520.4209 872.1575) 
(list 3520.4435 872.1678) 
(list 3520.4655 872.1781) 
(list 3520.4862 872.1883) 
(list 3520.505 872.1986) 
(list 3520.5213 872.2089) 
(list 3520.5346 872.2192) 
(list 3520.5446 872.2294) 
(list 3520.5507 872.2397) 
(list 3520.553 872.25) 
(list 3520.553 872.25)))
(apply 'command (append '("pline") coords '("c")))
(setq tap11 (ssadd (entlast) tap11))
(command "_mirror" (entlast) "" "3520,900" "3520,901" "No")
(setq tap11 (ssadd (entlast) tap11))
(setq coords (list 
(list 3521.106 871.88) 
(list 3520.553 871.88) 
(list 3520.553 871.8903) 
(list 3520.553 871.9006) 
(list 3520.553 871.9108) 
(list 3520.553 871.9211) 
(list 3520.553 871.9314) 
(list 3520.553 871.9417) 
(list 3520.553 871.9519) 
(list 3520.553 871.9622) 
(list 3520.553 871.9725) 
(list 3520.553 871.9828) 
(list 3520.553 871.9931) 
(list 3520.553 872.0033) 
(list 3520.553 872.0136) 
(list 3520.553 872.0239) 
(list 3520.553 872.0342) 
(list 3520.553 872.0444) 
(list 3520.553 872.0547) 
(list 3520.553 872.065) 
(list 3520.553 872.0753) 
(list 3520.553 872.0856) 
(list 3520.553 872.0958) 
(list 3520.553 872.1061) 
(list 3520.553 872.1164) 
(list 3520.553 872.1267) 
(list 3520.553 872.1369) 
(list 3520.553 872.1472) 
(list 3520.553 872.1575) 
(list 3520.553 872.1678) 
(list 3520.553 872.1781) 
(list 3520.553 872.1883) 
(list 3520.553 872.1986) 
(list 3520.553 872.2089) 
(list 3520.553 872.2192) 
(list 3520.553 872.2294) 
(list 3520.553 872.2397) 
(list 3520.553 872.25) 
(list 3521.106 872.25)))
(apply 'command (append '("pline") coords '("c")))
(setq tap11 (ssadd (entlast) tap11))
(command "_mirror" (entlast) "" "3520,900" "3520,901" "No")
(setq tap11 (ssadd (entlast) tap11))
(command "_block" "blktap11" "3520,900" tap11 "")
(command "_insert" "blktap11" "3520,900" "1" "1" "0")
(command "_insert" "blktap11" "3520,900" "1" "1" "180")
(setq uc11 nil)
(setq uc11 (ssadd))
(setq coords (list 
(list 0 -0.185) 
(list 0.135 -0.185) 
(list 0.135 -0.17472) 
(list 0.135 -0.16444) 
(list 0.135 -0.15417) 
(list 0.135 -0.14389) 
(list 0.135 -0.13361) 
(list 0.135 -0.12333) 
(list 0.135 -0.11306) 
(list 0.135 -0.10278) 
(list 0.135 -0.0925) 
(list 0.135 -0.082222) 
(list 0.135 -0.071944) 
(list 0.135 -0.061667) 
(list 0.135 -0.051389) 
(list 0.135 -0.041111) 
(list 0.135 -0.030833) 
(list 0.135 -0.020556) 
(list 0.135 -0.010278) 
(list 0.135 0) 
(list 0.135 0.010278) 
(list 0.135 0.020556) 
(list 0.135 0.030833) 
(list 0.135 0.041111) 
(list 0.135 0.051389) 
(list 0.135 0.061667) 
(list 0.135 0.071944) 
(list 0.135 0.082222) 
(list 0.135 0.0925) 
(list 0.135 0.10278) 
(list 0.135 0.11306) 
(list 0.135 0.12333) 
(list 0.135 0.13361) 
(list 0.135 0.14389) 
(list 0.135 0.15417) 
(list 0.135 0.16444) 
(list 0.135 0.17472) 
(list 0.135 0.185) 
(list 0 0.185)))
(apply 'command (append '("pline") coords '("c")))
(setq uc11 (ssadd (entlast) uc11))
(setq coords (list 
(list 1.106 -0.185) 
(list 0.553 -0.185) 
(list 0.551 -0.17472) 
(list 0.54504 -0.16444) 
(list 0.53531 -0.15417) 
(list 0.52212 -0.14389) 
(list 0.50585 -0.13361) 
(list 0.487 -0.12333) 
(list 0.46615 -0.11306) 
(list 0.44392 -0.10278) 
(list 0.421 -0.0925) 
(list 0.39808 -0.082222) 
(list 0.37585 -0.071944) 
(list 0.355 -0.061667) 
(list 0.33615 -0.051389) 
(list 0.31988 -0.041111) 
(list 0.30668 -0.030833) 
(list 0.29696 -0.020556) 
(list 0.29101 -0.010278) 
(list 0.289 0) 
(list 0.29101 0.010278) 
(list 0.29696 0.020556) 
(list 0.30668 0.030833) 
(list 0.31988 0.041111) 
(list 0.33615 0.051389) 
(list 0.355 0.061667) 
(list 0.37585 0.071944) 
(list 0.39808 0.082222) 
(list 0.421 0.0925) 
(list 0.44392 0.10278) 
(list 0.46615 0.11306) 
(list 0.487 0.12333) 
(list 0.50585 0.13361) 
(list 0.52212 0.14389) 
(list 0.53531 0.15417) 
(list 0.54504 0.16444) 
(list 0.551 0.17472) 
(list 0.553 0.185) 
(list 1.106 0.185)))
(apply 'command (append '("pline") coords '("c")))
(setq uc11 (ssadd (entlast) uc11))
(command "_block" "blkuc11" "0,0.185" uc11 "")
(command "_insert" "blkuc11" "3520,872.62" "1" "1" "0")
(command "_insert" "blkuc11" "3520,872.25" "1" "1" "180")
(command "_insert" "blkuc11" "3520,872.99" "1" "1" "0")
(command "_insert" "blkuc11" "3520,872.62" "1" "1" "180")
(command "_insert" "blkuc11" "3520,873.36" "1" "1" "0")
(command "_insert" "blkuc11" "3520,872.99" "1" "1" "180")
(command "_insert" "blkuc11" "3520,873.73" "1" "1" "0")
(command "_insert" "blkuc11" "3520,873.36" "1" "1" "180")
(command "_insert" "blkuc11" "3520,874.1" "1" "1" "0")
(command "_insert" "blkuc11" "3520,873.73" "1" "1" "180")
(command "_insert" "blkuc11" "3520,874.47" "1" "1" "0")
(command "_insert" "blkuc11" "3520,874.1" "1" "1" "180")
(command "_insert" "blkuc11" "3520,874.84" "1" "1" "0")
(command "_insert" "blkuc11" "3520,874.47" "1" "1" "180")
(command "_insert" "blkuc11" "3520,875.21" "1" "1" "0")
(command "_insert" "blkuc11" "3520,874.84" "1" "1" "180")
(command "_insert" "blkuc11" "3520,875.58" "1" "1" "0")
(command "_insert" "blkuc11" "3520,875.21" "1" "1" "180")
(command "_insert" "blkuc11" "3520,875.95" "1" "1" "0")
(command "_insert" "blkuc11" "3520,875.58" "1" "1" "180")
(command "_insert" "blkuc11" "3520,876.32" "1" "1" "0")
(command "_insert" "blkuc11" "3520,875.95" "1" "1" "180")
(command "_insert" "blkuc11" "3520,876.69" "1" "1" "0")
(command "_insert" "blkuc11" "3520,876.32" "1" "1" "180")
(command "_insert" "blkuc11" "3520,877.06" "1" "1" "0")
(command "_insert" "blkuc11" "3520,876.69" "1" "1" "180")
(command "_insert" "blkuc11" "3520,877.43" "1" "1" "0")
(command "_insert" "blkuc11" "3520,877.06" "1" "1" "180")
(command "_insert" "blkuc11" "3520,877.8" "1" "1" "0")
(command "_insert" "blkuc11" "3520,877.43" "1" "1" "180")
(command "_insert" "blkuc11" "3520,878.17" "1" "1" "0")
(command "_insert" "blkuc11" "3520,877.8" "1" "1" "180")
(command "_insert" "blkuc11" "3520,878.54" "1" "1" "0")
(command "_insert" "blkuc11" "3520,878.17" "1" "1" "180")
(command "_insert" "blkuc11" "3520,878.91" "1" "1" "0")
(command "_insert" "blkuc11" "3520,878.54" "1" "1" "180")
(command "_insert" "blkuc11" "3520,879.28" "1" "1" "0")
(command "_insert" "blkuc11" "3520,878.91" "1" "1" "180")
(command "_insert" "blkuc11" "3520,879.65" "1" "1" "0")
(command "_insert" "blkuc11" "3520,879.28" "1" "1" "180")
(command "_insert" "blkuc11" "3520,880.02" "1" "1" "0")
(command "_insert" "blkuc11" "3520,879.65" "1" "1" "180")
(command "_insert" "blkuc11" "3520,880.39" "1" "1" "0")
(command "_insert" "blkuc11" "3520,880.02" "1" "1" "180")
(command "_insert" "blkuc11" "3520,880.76" "1" "1" "0")
(command "_insert" "blkuc11" "3520,880.39" "1" "1" "180")
(command "_insert" "blkuc11" "3520,881.13" "1" "1" "0")
(command "_insert" "blkuc11" "3520,880.76" "1" "1" "180")
(command "_insert" "blkuc11" "3520,881.5" "1" "1" "0")
(command "_insert" "blkuc11" "3520,881.13" "1" "1" "180")
(command "_insert" "blkuc11" "3520,881.87" "1" "1" "0")
(command "_insert" "blkuc11" "3520,881.5" "1" "1" "180")
(command "_insert" "blkuc11" "3520,882.24" "1" "1" "0")
(command "_insert" "blkuc11" "3520,881.87" "1" "1" "180")
(command "_insert" "blkuc11" "3520,882.61" "1" "1" "0")
(command "_insert" "blkuc11" "3520,882.24" "1" "1" "180")
(command "_insert" "blkuc11" "3520,882.98" "1" "1" "0")
(command "_insert" "blkuc11" "3520,882.61" "1" "1" "180")
(command "_insert" "blkuc11" "3520,883.35" "1" "1" "0")
(command "_insert" "blkuc11" "3520,882.98" "1" "1" "180")
(command "_insert" "blkuc11" "3520,883.72" "1" "1" "0")
(command "_insert" "blkuc11" "3520,883.35" "1" "1" "180")
(command "_insert" "blkuc11" "3520,884.09" "1" "1" "0")
(command "_insert" "blkuc11" "3520,883.72" "1" "1" "180")
(command "_insert" "blkuc11" "3520,884.46" "1" "1" "0")
(command "_insert" "blkuc11" "3520,884.09" "1" "1" "180")
(command "_insert" "blkuc11" "3520,884.83" "1" "1" "0")
(command "_insert" "blkuc11" "3520,884.46" "1" "1" "180")
(command "_insert" "blkuc11" "3520,885.2" "1" "1" "0")
(command "_insert" "blkuc11" "3520,884.83" "1" "1" "180")
(command "_insert" "blkuc11" "3520,885.57" "1" "1" "0")
(command "_insert" "blkuc11" "3520,885.2" "1" "1" "180")
(command "_insert" "blkuc11" "3520,885.94" "1" "1" "0")
(command "_insert" "blkuc11" "3520,885.57" "1" "1" "180")
(command "_insert" "blkuc11" "3520,886.31" "1" "1" "0")
(command "_insert" "blkuc11" "3520,885.94" "1" "1" "180")
(command "_insert" "blkuc11" "3520,886.68" "1" "1" "0")
(command "_insert" "blkuc11" "3520,886.31" "1" "1" "180")
(command "_insert" "blkuc11" "3520,887.05" "1" "1" "0")
(command "_insert" "blkuc11" "3520,886.68" "1" "1" "180")
(command "_insert" "blkuc11" "3520,887.42" "1" "1" "0")
(command "_insert" "blkuc11" "3520,887.05" "1" "1" "180")
(command "_insert" "blkuc11" "3520,887.79" "1" "1" "0")
(command "_insert" "blkuc11" "3520,887.42" "1" "1" "180")
(command "_insert" "blkuc11" "3520,888.16" "1" "1" "0")
(command "_insert" "blkuc11" "3520,887.79" "1" "1" "180")
(command "_insert" "blkuc11" "3520,888.53" "1" "1" "0")
(command "_insert" "blkuc11" "3520,888.16" "1" "1" "180")
(command "_insert" "blkuc11" "3520,888.9" "1" "1" "0")
(command "_insert" "blkuc11" "3520,888.53" "1" "1" "180")
(command "_insert" "blkuc11" "3520,889.27" "1" "1" "0")
(command "_insert" "blkuc11" "3520,888.9" "1" "1" "180")
(command "_insert" "blkuc11" "3520,889.64" "1" "1" "0")
(command "_insert" "blkuc11" "3520,889.27" "1" "1" "180")
(command "_insert" "blkuc11" "3520,890.01" "1" "1" "0")
(command "_insert" "blkuc11" "3520,889.64" "1" "1" "180")
(command "_insert" "blkuc11" "3520,890.38" "1" "1" "0")
(command "_insert" "blkuc11" "3520,890.01" "1" "1" "180")
(command "_insert" "blkuc11" "3520,890.75" "1" "1" "0")
(command "_insert" "blkuc11" "3520,890.38" "1" "1" "180")
(command "_insert" "blkuc11" "3520,891.12" "1" "1" "0")
(command "_insert" "blkuc11" "3520,890.75" "1" "1" "180")
(command "_insert" "blkuc11" "3520,891.49" "1" "1" "0")
(command "_insert" "blkuc11" "3520,891.12" "1" "1" "180")
(command "_insert" "blkuc11" "3520,891.86" "1" "1" "0")
(command "_insert" "blkuc11" "3520,891.49" "1" "1" "180")
(command "_insert" "blkuc11" "3520,892.23" "1" "1" "0")
(command "_insert" "blkuc11" "3520,891.86" "1" "1" "180")
(command "_insert" "blkuc11" "3520,892.6" "1" "1" "0")
(command "_insert" "blkuc11" "3520,892.23" "1" "1" "180")
(command "_insert" "blkuc11" "3520,892.97" "1" "1" "0")
(command "_insert" "blkuc11" "3520,892.6" "1" "1" "180")
(command "_insert" "blkuc11" "3520,893.34" "1" "1" "0")
(command "_insert" "blkuc11" "3520,892.97" "1" "1" "180")
(command "_insert" "blkuc11" "3520,893.71" "1" "1" "0")
(command "_insert" "blkuc11" "3520,893.34" "1" "1" "180")
(command "_insert" "blkuc11" "3520,894.08" "1" "1" "0")
(command "_insert" "blkuc11" "3520,893.71" "1" "1" "180")
(command "_insert" "blkuc11" "3520,894.45" "1" "1" "0")
(command "_insert" "blkuc11" "3520,894.08" "1" "1" "180")
(command "_insert" "blkuc11" "3520,894.82" "1" "1" "0")
(command "_insert" "blkuc11" "3520,894.45" "1" "1" "180")
(command "_insert" "blkuc11" "3520,895.19" "1" "1" "0")
(command "_insert" "blkuc11" "3520,894.82" "1" "1" "180")
(command "_insert" "blkuc11" "3520,895.56" "1" "1" "0")
(command "_insert" "blkuc11" "3520,895.19" "1" "1" "180")
(command "_insert" "blkuc11" "3520,895.93" "1" "1" "0")
(command "_insert" "blkuc11" "3520,895.56" "1" "1" "180")
(command "_insert" "blkuc11" "3520,896.3" "1" "1" "0")
(command "_insert" "blkuc11" "3520,895.93" "1" "1" "180")
(command "_insert" "blkuc11" "3520,896.67" "1" "1" "0")
(command "_insert" "blkuc11" "3520,896.3" "1" "1" "180")
(command "_insert" "blkuc11" "3520,897.04" "1" "1" "0")
(command "_insert" "blkuc11" "3520,896.67" "1" "1" "180")
(command "_insert" "blkuc11" "3520,897.41" "1" "1" "0")
(command "_insert" "blkuc11" "3520,897.04" "1" "1" "180")
(command "_insert" "blkuc11" "3520,897.78" "1" "1" "0")
(command "_insert" "blkuc11" "3520,897.41" "1" "1" "180")
(command "_insert" "blkuc11" "3520,898.15" "1" "1" "0")
(command "_insert" "blkuc11" "3520,897.78" "1" "1" "180")
(command "_insert" "blkuc11" "3520,898.52" "1" "1" "0")
(command "_insert" "blkuc11" "3520,898.15" "1" "1" "180")
(command "_insert" "blkuc11" "3520,898.89" "1" "1" "0")
(command "_insert" "blkuc11" "3520,898.52" "1" "1" "180")
(command "_insert" "blkuc11" "3520,899.26" "1" "1" "0")
(command "_insert" "blkuc11" "3520,898.89" "1" "1" "180")
(command "_insert" "blkuc11" "3520,899.63" "1" "1" "0")
(command "_insert" "blkuc11" "3520,899.26" "1" "1" "180")
(command "_insert" "blkuc11" "3520,900" "1" "1" "0")
(command "_insert" "blkuc11" "3520,899.63" "1" "1" "180")
(command "_insert" "blkuc11" "3520,900.37" "1" "1" "0")
(command "_insert" "blkuc11" "3520,900" "1" "1" "180")
(command "_insert" "blkuc11" "3520,900.74" "1" "1" "0")
(command "_insert" "blkuc11" "3520,900.37" "1" "1" "180")
(command "_insert" "blkuc11" "3520,901.11" "1" "1" "0")
(command "_insert" "blkuc11" "3520,900.74" "1" "1" "180")
(command "_insert" "blkuc11" "3520,901.48" "1" "1" "0")
(command "_insert" "blkuc11" "3520,901.11" "1" "1" "180")
(command "_insert" "blkuc11" "3520,901.85" "1" "1" "0")
(command "_insert" "blkuc11" "3520,901.48" "1" "1" "180")
(command "_insert" "blkuc11" "3520,902.22" "1" "1" "0")
(command "_insert" "blkuc11" "3520,901.85" "1" "1" "180")
(command "_insert" "blkuc11" "3520,902.59" "1" "1" "0")
(command "_insert" "blkuc11" "3520,902.22" "1" "1" "180")
(command "_insert" "blkuc11" "3520,902.96" "1" "1" "0")
(command "_insert" "blkuc11" "3520,902.59" "1" "1" "180")
(command "_insert" "blkuc11" "3520,903.33" "1" "1" "0")
(command "_insert" "blkuc11" "3520,902.96" "1" "1" "180")
(command "_insert" "blkuc11" "3520,903.7" "1" "1" "0")
(command "_insert" "blkuc11" "3520,903.33" "1" "1" "180")
(command "_insert" "blkuc11" "3520,904.07" "1" "1" "0")
(command "_insert" "blkuc11" "3520,903.7" "1" "1" "180")
(command "_insert" "blkuc11" "3520,904.44" "1" "1" "0")
(command "_insert" "blkuc11" "3520,904.07" "1" "1" "180")
(command "_insert" "blkuc11" "3520,904.81" "1" "1" "0")
(command "_insert" "blkuc11" "3520,904.44" "1" "1" "180")
(command "_insert" "blkuc11" "3520,905.18" "1" "1" "0")
(command "_insert" "blkuc11" "3520,904.81" "1" "1" "180")
(command "_insert" "blkuc11" "3520,905.55" "1" "1" "0")
(command "_insert" "blkuc11" "3520,905.18" "1" "1" "180")
(command "_insert" "blkuc11" "3520,905.92" "1" "1" "0")
(command "_insert" "blkuc11" "3520,905.55" "1" "1" "180")
(command "_insert" "blkuc11" "3520,906.29" "1" "1" "0")
(command "_insert" "blkuc11" "3520,905.92" "1" "1" "180")
(command "_insert" "blkuc11" "3520,906.66" "1" "1" "0")
(command "_insert" "blkuc11" "3520,906.29" "1" "1" "180")
(command "_insert" "blkuc11" "3520,907.03" "1" "1" "0")
(command "_insert" "blkuc11" "3520,906.66" "1" "1" "180")
(command "_insert" "blkuc11" "3520,907.4" "1" "1" "0")
(command "_insert" "blkuc11" "3520,907.03" "1" "1" "180")
(command "_insert" "blkuc11" "3520,907.77" "1" "1" "0")
(command "_insert" "blkuc11" "3520,907.4" "1" "1" "180")
(command "_insert" "blkuc11" "3520,908.14" "1" "1" "0")
(command "_insert" "blkuc11" "3520,907.77" "1" "1" "180")
(command "_insert" "blkuc11" "3520,908.51" "1" "1" "0")
(command "_insert" "blkuc11" "3520,908.14" "1" "1" "180")
(command "_insert" "blkuc11" "3520,908.88" "1" "1" "0")
(command "_insert" "blkuc11" "3520,908.51" "1" "1" "180")
(command "_insert" "blkuc11" "3520,909.25" "1" "1" "0")
(command "_insert" "blkuc11" "3520,908.88" "1" "1" "180")
(command "_insert" "blkuc11" "3520,909.62" "1" "1" "0")
(command "_insert" "blkuc11" "3520,909.25" "1" "1" "180")
(command "_insert" "blkuc11" "3520,909.99" "1" "1" "0")
(command "_insert" "blkuc11" "3520,909.62" "1" "1" "180")
(command "_insert" "blkuc11" "3520,910.36" "1" "1" "0")
(command "_insert" "blkuc11" "3520,909.99" "1" "1" "180")
(command "_insert" "blkuc11" "3520,910.73" "1" "1" "0")
(command "_insert" "blkuc11" "3520,910.36" "1" "1" "180")
(command "_insert" "blkuc11" "3520,911.1" "1" "1" "0")
(command "_insert" "blkuc11" "3520,910.73" "1" "1" "180")
(command "_insert" "blkuc11" "3520,911.47" "1" "1" "0")
(command "_insert" "blkuc11" "3520,911.1" "1" "1" "180")
(command "_insert" "blkuc11" "3520,911.84" "1" "1" "0")
(command "_insert" "blkuc11" "3520,911.47" "1" "1" "180")
(command "_insert" "blkuc11" "3520,912.21" "1" "1" "0")
(command "_insert" "blkuc11" "3520,911.84" "1" "1" "180")
(command "_insert" "blkuc11" "3520,912.58" "1" "1" "0")
(command "_insert" "blkuc11" "3520,912.21" "1" "1" "180")
(command "_insert" "blkuc11" "3520,912.95" "1" "1" "0")
(command "_insert" "blkuc11" "3520,912.58" "1" "1" "180")
(command "_insert" "blkuc11" "3520,913.32" "1" "1" "0")
(command "_insert" "blkuc11" "3520,912.95" "1" "1" "180")
(command "_insert" "blkuc11" "3520,913.69" "1" "1" "0")
(command "_insert" "blkuc11" "3520,913.32" "1" "1" "180")
(command "_insert" "blkuc11" "3520,914.06" "1" "1" "0")
(command "_insert" "blkuc11" "3520,913.69" "1" "1" "180")
(command "_insert" "blkuc11" "3520,914.43" "1" "1" "0")
(command "_insert" "blkuc11" "3520,914.06" "1" "1" "180")
(command "_insert" "blkuc11" "3520,914.8" "1" "1" "0")
(command "_insert" "blkuc11" "3520,914.43" "1" "1" "180")
(command "_insert" "blkuc11" "3520,915.17" "1" "1" "0")
(command "_insert" "blkuc11" "3520,914.8" "1" "1" "180")
(command "_insert" "blkuc11" "3520,915.54" "1" "1" "0")
(command "_insert" "blkuc11" "3520,915.17" "1" "1" "180")
(command "_insert" "blkuc11" "3520,915.91" "1" "1" "0")
(command "_insert" "blkuc11" "3520,915.54" "1" "1" "180")
(command "_insert" "blkuc11" "3520,916.28" "1" "1" "0")
(command "_insert" "blkuc11" "3520,915.91" "1" "1" "180")
(command "_insert" "blkuc11" "3520,916.65" "1" "1" "0")
(command "_insert" "blkuc11" "3520,916.28" "1" "1" "180")
(command "_insert" "blkuc11" "3520,917.02" "1" "1" "0")
(command "_insert" "blkuc11" "3520,916.65" "1" "1" "180")
(command "_insert" "blkuc11" "3520,917.39" "1" "1" "0")
(command "_insert" "blkuc11" "3520,917.02" "1" "1" "180")
(command "_insert" "blkuc11" "3520,917.76" "1" "1" "0")
(command "_insert" "blkuc11" "3520,917.39" "1" "1" "180")
(command "_insert" "blkuc11" "3520,918.13" "1" "1" "0")
(command "_insert" "blkuc11" "3520,917.76" "1" "1" "180")
(command "_insert" "blkuc11" "3520,918.5" "1" "1" "0")
(command "_insert" "blkuc11" "3520,918.13" "1" "1" "180")
(command "_insert" "blkuc11" "3520,918.87" "1" "1" "0")
(command "_insert" "blkuc11" "3520,918.5" "1" "1" "180")
(command "_insert" "blkuc11" "3520,919.24" "1" "1" "0")
(command "_insert" "blkuc11" "3520,918.87" "1" "1" "180")
(command "_insert" "blkuc11" "3520,919.61" "1" "1" "0")
(command "_insert" "blkuc11" "3520,919.24" "1" "1" "180")
(command "_insert" "blkuc11" "3520,919.98" "1" "1" "0")
(command "_insert" "blkuc11" "3520,919.61" "1" "1" "180")
(command "_insert" "blkuc11" "3520,920.35" "1" "1" "0")
(command "_insert" "blkuc11" "3520,919.98" "1" "1" "180")
(command "_insert" "blkuc11" "3520,920.72" "1" "1" "0")
(command "_insert" "blkuc11" "3520,920.35" "1" "1" "180")
(command "_insert" "blkuc11" "3520,921.09" "1" "1" "0")
(command "_insert" "blkuc11" "3520,920.72" "1" "1" "180")
(command "_insert" "blkuc11" "3520,921.46" "1" "1" "0")
(command "_insert" "blkuc11" "3520,921.09" "1" "1" "180")
(command "_insert" "blkuc11" "3520,921.83" "1" "1" "0")
(command "_insert" "blkuc11" "3520,921.46" "1" "1" "180")
(command "_insert" "blkuc11" "3520,922.2" "1" "1" "0")
(command "_insert" "blkuc11" "3520,921.83" "1" "1" "180")
(command "_insert" "blkuc11" "3520,922.57" "1" "1" "0")
(command "_insert" "blkuc11" "3520,922.2" "1" "1" "180")
(command "_insert" "blkuc11" "3520,922.94" "1" "1" "0")
(command "_insert" "blkuc11" "3520,922.57" "1" "1" "180")
(command "_insert" "blkuc11" "3520,923.31" "1" "1" "0")
(command "_insert" "blkuc11" "3520,922.94" "1" "1" "180")
(command "_insert" "blkuc11" "3520,923.68" "1" "1" "0")
(command "_insert" "blkuc11" "3520,923.31" "1" "1" "180")
(command "_insert" "blkuc11" "3520,924.05" "1" "1" "0")
(command "_insert" "blkuc11" "3520,923.68" "1" "1" "180")
(command "_insert" "blkuc11" "3520,924.42" "1" "1" "0")
(command "_insert" "blkuc11" "3520,924.05" "1" "1" "180")
(command "_insert" "blkuc11" "3520,924.79" "1" "1" "0")
(command "_insert" "blkuc11" "3520,924.42" "1" "1" "180")
(command "_insert" "blkuc11" "3520,925.16" "1" "1" "0")
(command "_insert" "blkuc11" "3520,924.79" "1" "1" "180")
(command "_insert" "blkuc11" "3520,925.53" "1" "1" "0")
(command "_insert" "blkuc11" "3520,925.16" "1" "1" "180")
(command "_insert" "blkuc11" "3520,925.9" "1" "1" "0")
(command "_insert" "blkuc11" "3520,925.53" "1" "1" "180")
(command "_insert" "blkuc11" "3520,926.27" "1" "1" "0")
(command "_insert" "blkuc11" "3520,925.9" "1" "1" "180")
(command "_insert" "blkuc11" "3520,926.64" "1" "1" "0")
(command "_insert" "blkuc11" "3520,926.27" "1" "1" "180")
(command "_insert" "blkuc11" "3520,927.01" "1" "1" "0")
(command "_insert" "blkuc11" "3520,926.64" "1" "1" "180")
(command "_insert" "blkuc11" "3520,927.38" "1" "1" "0")
(command "_insert" "blkuc11" "3520,927.01" "1" "1" "180")
(command "_insert" "blkuc11" "3520,927.75" "1" "1" "0")
(command "_insert" "blkuc11" "3520,927.38" "1" "1" "180")
(command "_layer" "set" "phccover" "")
(command "_rectangle" "3518.894,933.3" "3521.106,866.7")
(command "_layer" "set" "nitride" "")
(setq phc11 currobj)
(command "_layer" "set" "cover" "")
(command "_rectangle" "3518.894,836.7" "3521.106,963.3")
(command "_layer" "set" "nitride" "")
(command "_layer" "set" "text" "")
(command "_circle" "3517.944,846.7" "0.075")
(command "_circle" "3517.569,846.7" "0.15")
(command "_circle" "3517.194,846.7" "0.075")
(command "_circle" "3516.819,846.7" "0.15")
(command "_circle" "3517.944,848.7" "0.075")
(command "_circle" "3517.569,848.7" "0.075")
(command "_circle" "3517.194,848.7" "0.15")
(command "_circle" "3516.819,848.7" "0.15")
(command "_circle" "3517.944,850.7" "0.075")
(command "_circle" "3517.569,850.7" "0.15")
(command "_circle" "3517.194,850.7" "0.15")
(command "_circle" "3516.819,850.7" "0.15")
(command "_circle" "3517.944,852.7" "0.075")
(command "_circle" "3517.569,852.7" "0.075")
(command "_circle" "3517.194,852.7" "0.075")
(command "_circle" "3516.819,852.7" "0.075")
(command "_circle" "3516.444,852.7" "0.15")
(command "_circle" "3517.944,854.7" "0.075")
(command "_circle" "3517.569,854.7" "0.15")
(command "_circle" "3517.194,854.7" "0.075")
(command "_circle" "3516.819,854.7" "0.075")
(command "_circle" "3516.444,854.7" "0.15")
(command "_circle" "3517.944,856.7" "0.075")
(command "_circle" "3517.569,856.7" "0.075")
(command "_circle" "3517.194,856.7" "0.15")
(command "_circle" "3516.819,856.7" "0.075")
(command "_circle" "3516.444,856.7" "0.15")
(command "_circle" "3517.944,858.7" "0.075")
(command "_circle" "3517.569,858.7" "0.15")
(command "_circle" "3517.194,858.7" "0.15")
(command "_circle" "3516.819,858.7" "0.075")
(command "_circle" "3516.444,858.7" "0.15")
(command "_circle" "3517.944,860.7" "0.075")
(command "_circle" "3517.569,860.7" "0.075")
(command "_circle" "3517.194,860.7" "0.075")
(command "_circle" "3516.819,860.7" "0.15")
(command "_circle" "3516.444,860.7" "0.15")
(command "_circle" "3517.944,862.7" "0.075")
(command "_circle" "3517.569,862.7" "0.15")
(command "_circle" "3517.194,862.7" "0.075")
(command "_circle" "3516.819,862.7" "0.15")
(command "_circle" "3516.444,862.7" "0.15")
(command "_circle" "3517.944,864.7" "0.075")
(command "_circle" "3517.569,864.7" "0.075")
(command "_circle" "3517.194,864.7" "0.15")
(command "_circle" "3516.819,864.7" "0.15")
(command "_circle" "3516.444,864.7" "0.15")
(command "_circle" "3517.944,866.7" "0.075")
(command "_circle" "3517.569,866.7" "0.15")
(command "_circle" "3517.194,866.7" "0.15")
(command "_circle" "3516.819,866.7" "0.15")
(command "_circle" "3516.444,866.7" "0.15")
(command "_circle" "3517.944,868.7" "0.075")
(command "_circle" "3517.569,868.7" "0.075")
(command "_circle" "3517.194,868.7" "0.075")
(command "_circle" "3516.819,868.7" "0.075")
(command "_circle" "3516.444,868.7" "0.075")
(command "_circle" "3516.069,868.7" "0.15")
(command "_circle" "3517.944,870.7" "0.075")
(command "_circle" "3517.569,870.7" "0.15")
(command "_circle" "3517.194,870.7" "0.075")
(command "_circle" "3516.819,870.7" "0.075")
(command "_circle" "3516.444,870.7" "0.075")
(command "_circle" "3516.069,870.7" "0.15")
(command "_circle" "3517.944,872.7" "0.075")
(command "_circle" "3517.569,872.7" "0.075")
(command "_circle" "3517.194,872.7" "0.15")
(command "_circle" "3516.819,872.7" "0.075")
(command "_circle" "3516.444,872.7" "0.075")
(command "_circle" "3516.069,872.7" "0.15")
(command "_circle" "3517.944,874.7" "0.075")
(command "_circle" "3517.569,874.7" "0.15")
(command "_circle" "3517.194,874.7" "0.15")
(command "_circle" "3516.819,874.7" "0.075")
(command "_circle" "3516.444,874.7" "0.075")
(command "_circle" "3516.069,874.7" "0.15")
(command "_circle" "3517.944,876.7" "0.075")
(command "_circle" "3517.569,876.7" "0.075")
(command "_circle" "3517.194,876.7" "0.075")
(command "_circle" "3516.819,876.7" "0.15")
(command "_circle" "3516.444,876.7" "0.075")
(command "_circle" "3516.069,876.7" "0.15")
(command "_circle" "3517.944,878.7" "0.075")
(command "_circle" "3517.569,878.7" "0.15")
(command "_circle" "3517.194,878.7" "0.075")
(command "_circle" "3516.819,878.7" "0.15")
(command "_circle" "3516.444,878.7" "0.075")
(command "_circle" "3516.069,878.7" "0.15")
(command "_circle" "3517.944,880.7" "0.075")
(command "_circle" "3517.569,880.7" "0.075")
(command "_circle" "3517.194,880.7" "0.15")
(command "_circle" "3516.819,880.7" "0.15")
(command "_circle" "3516.444,880.7" "0.075")
(command "_circle" "3516.069,880.7" "0.15")
(command "_circle" "3517.944,882.7" "0.075")
(command "_circle" "3517.569,882.7" "0.15")
(command "_circle" "3517.194,882.7" "0.15")
(command "_circle" "3516.819,882.7" "0.15")
(command "_circle" "3516.444,882.7" "0.075")
(command "_circle" "3516.069,882.7" "0.15")
(command "_circle" "3517.944,884.7" "0.075")
(command "_circle" "3517.569,884.7" "0.075")
(command "_circle" "3517.194,884.7" "0.075")
(command "_circle" "3516.819,884.7" "0.075")
(command "_circle" "3516.444,884.7" "0.15")
(command "_circle" "3516.069,884.7" "0.15")
(command "_circle" "3517.944,886.7" "0.075")
(command "_circle" "3517.569,886.7" "0.15")
(command "_circle" "3517.194,886.7" "0.075")
(command "_circle" "3516.819,886.7" "0.075")
(command "_circle" "3516.444,886.7" "0.15")
(command "_circle" "3516.069,886.7" "0.15")
(command "_circle" "3517.944,888.7" "0.075")
(command "_circle" "3517.569,888.7" "0.075")
(command "_circle" "3517.194,888.7" "0.15")
(command "_circle" "3516.819,888.7" "0.075")
(command "_circle" "3516.444,888.7" "0.15")
(command "_circle" "3516.069,888.7" "0.15")
(command "_circle" "3517.944,890.7" "0.075")
(command "_circle" "3517.569,890.7" "0.15")
(command "_circle" "3517.194,890.7" "0.15")
(command "_circle" "3516.819,890.7" "0.075")
(command "_circle" "3516.444,890.7" "0.15")
(command "_circle" "3516.069,890.7" "0.15")
(command "_circle" "3517.944,892.7" "0.075")
(command "_circle" "3517.569,892.7" "0.075")
(command "_circle" "3517.194,892.7" "0.075")
(command "_circle" "3516.819,892.7" "0.15")
(command "_circle" "3516.444,892.7" "0.15")
(command "_circle" "3516.069,892.7" "0.15")
(command "_circle" "3517.944,894.7" "0.075")
(command "_circle" "3517.569,894.7" "0.15")
(command "_circle" "3517.194,894.7" "0.075")
(command "_circle" "3516.819,894.7" "0.15")
(command "_circle" "3516.444,894.7" "0.15")
(command "_circle" "3516.069,894.7" "0.15")
(command "_circle" "3517.944,896.7" "0.075")
(command "_circle" "3517.569,896.7" "0.075")
(command "_circle" "3517.194,896.7" "0.15")
(command "_circle" "3516.819,896.7" "0.15")
(command "_circle" "3516.444,896.7" "0.15")
(command "_circle" "3516.069,896.7" "0.15")
(command "_circle" "3517.944,898.7" "0.075")
(command "_circle" "3517.569,898.7" "0.15")
(command "_circle" "3517.194,898.7" "0.15")
(command "_circle" "3516.819,898.7" "0.15")
(command "_circle" "3516.444,898.7" "0.15")
(command "_circle" "3516.069,898.7" "0.15")
(command "_circle" "3517.944,900.7" "0.075")
(command "_circle" "3517.569,900.7" "0.075")
(command "_circle" "3517.194,900.7" "0.075")
(command "_circle" "3516.819,900.7" "0.075")
(command "_circle" "3516.444,900.7" "0.075")
(command "_circle" "3516.069,900.7" "0.075")
(command "_circle" "3515.694,900.7" "0.15")
(command "_circle" "3517.944,902.7" "0.075")
(command "_circle" "3517.569,902.7" "0.15")
(command "_circle" "3517.194,902.7" "0.075")
(command "_circle" "3516.819,902.7" "0.075")
(command "_circle" "3516.444,902.7" "0.075")
(command "_circle" "3516.069,902.7" "0.075")
(command "_circle" "3515.694,902.7" "0.15")
(command "_circle" "3517.944,904.7" "0.075")
(command "_circle" "3517.569,904.7" "0.075")
(command "_circle" "3517.194,904.7" "0.15")
(command "_circle" "3516.819,904.7" "0.075")
(command "_circle" "3516.444,904.7" "0.075")
(command "_circle" "3516.069,904.7" "0.075")
(command "_circle" "3515.694,904.7" "0.15")
(command "_circle" "3517.944,906.7" "0.075")
(command "_circle" "3517.569,906.7" "0.15")
(command "_circle" "3517.194,906.7" "0.15")
(command "_circle" "3516.819,906.7" "0.075")
(command "_circle" "3516.444,906.7" "0.075")
(command "_circle" "3516.069,906.7" "0.075")
(command "_circle" "3515.694,906.7" "0.15")
(command "_circle" "3517.944,908.7" "0.075")
(command "_circle" "3517.569,908.7" "0.075")
(command "_circle" "3517.194,908.7" "0.075")
(command "_circle" "3516.819,908.7" "0.15")
(command "_circle" "3516.444,908.7" "0.075")
(command "_circle" "3516.069,908.7" "0.075")
(command "_circle" "3515.694,908.7" "0.15")
(command "_circle" "3517.944,910.7" "0.075")
(command "_circle" "3517.569,910.7" "0.15")
(command "_circle" "3517.194,910.7" "0.075")
(command "_circle" "3516.819,910.7" "0.15")
(command "_circle" "3516.444,910.7" "0.075")
(command "_circle" "3516.069,910.7" "0.075")
(command "_circle" "3515.694,910.7" "0.15")
(command "_circle" "3517.944,912.7" "0.075")
(command "_circle" "3517.569,912.7" "0.075")
(command "_circle" "3517.194,912.7" "0.15")
(command "_circle" "3516.819,912.7" "0.15")
(command "_circle" "3516.444,912.7" "0.075")
(command "_circle" "3516.069,912.7" "0.075")
(command "_circle" "3515.694,912.7" "0.15")
(command "_circle" "3517.944,914.7" "0.075")
(command "_circle" "3517.569,914.7" "0.15")
(command "_circle" "3517.194,914.7" "0.15")
(command "_circle" "3516.819,914.7" "0.15")
(command "_circle" "3516.444,914.7" "0.075")
(command "_circle" "3516.069,914.7" "0.075")
(command "_circle" "3515.694,914.7" "0.15")
(command "_circle" "3517.944,916.7" "0.075")
(command "_circle" "3517.569,916.7" "0.075")
(command "_circle" "3517.194,916.7" "0.075")
(command "_circle" "3516.819,916.7" "0.075")
(command "_circle" "3516.444,916.7" "0.15")
(command "_circle" "3516.069,916.7" "0.075")
(command "_circle" "3515.694,916.7" "0.15")
(command "_circle" "3517.944,918.7" "0.075")
(command "_circle" "3517.569,918.7" "0.15")
(command "_circle" "3517.194,918.7" "0.075")
(command "_circle" "3516.819,918.7" "0.075")
(command "_circle" "3516.444,918.7" "0.15")
(command "_circle" "3516.069,918.7" "0.075")
(command "_circle" "3515.694,918.7" "0.15")
(command "_circle" "3517.944,920.7" "0.075")
(command "_circle" "3517.569,920.7" "0.075")
(command "_circle" "3517.194,920.7" "0.15")
(command "_circle" "3516.819,920.7" "0.075")
(command "_circle" "3516.444,920.7" "0.15")
(command "_circle" "3516.069,920.7" "0.075")
(command "_circle" "3515.694,920.7" "0.15")
(command "_circle" "3517.944,922.7" "0.075")
(command "_circle" "3517.569,922.7" "0.15")
(command "_circle" "3517.194,922.7" "0.15")
(command "_circle" "3516.819,922.7" "0.075")
(command "_circle" "3516.444,922.7" "0.15")
(command "_circle" "3516.069,922.7" "0.075")
(command "_circle" "3515.694,922.7" "0.15")
(command "_circle" "3517.944,924.7" "0.075")
(command "_circle" "3517.569,924.7" "0.075")
(command "_circle" "3517.194,924.7" "0.075")
(command "_circle" "3516.819,924.7" "0.15")
(command "_circle" "3516.444,924.7" "0.15")
(command "_circle" "3516.069,924.7" "0.075")
(command "_circle" "3515.694,924.7" "0.15")
(command "_circle" "3517.944,926.7" "0.075")
(command "_circle" "3517.569,926.7" "0.15")
(command "_circle" "3517.194,926.7" "0.075")
(command "_circle" "3516.819,926.7" "0.15")
(command "_circle" "3516.444,926.7" "0.15")
(command "_circle" "3516.069,926.7" "0.075")
(command "_circle" "3515.694,926.7" "0.15")
(command "_circle" "3517.944,928.7" "0.075")
(command "_circle" "3517.569,928.7" "0.075")
(command "_circle" "3517.194,928.7" "0.15")
(command "_circle" "3516.819,928.7" "0.15")
(command "_circle" "3516.444,928.7" "0.15")
(command "_circle" "3516.069,928.7" "0.075")
(command "_circle" "3515.694,928.7" "0.15")
(command "_circle" "3517.944,930.7" "0.075")
(command "_circle" "3517.569,930.7" "0.15")
(command "_circle" "3517.194,930.7" "0.15")
(command "_circle" "3516.819,930.7" "0.15")
(command "_circle" "3516.444,930.7" "0.15")
(command "_circle" "3516.069,930.7" "0.075")
(command "_circle" "3515.694,930.7" "0.15")
(command "_circle" "3517.944,932.7" "0.075")
(command "_circle" "3517.569,932.7" "0.075")
(command "_circle" "3517.194,932.7" "0.075")
(command "_circle" "3516.819,932.7" "0.075")
(command "_circle" "3516.444,932.7" "0.075")
(command "_circle" "3516.069,932.7" "0.15")
(command "_circle" "3515.694,932.7" "0.15")
(command "_circle" "3517.944,934.7" "0.075")
(command "_circle" "3517.569,934.7" "0.15")
(command "_circle" "3517.194,934.7" "0.075")
(command "_circle" "3516.819,934.7" "0.075")
(command "_circle" "3516.444,934.7" "0.075")
(command "_circle" "3516.069,934.7" "0.15")
(command "_circle" "3515.694,934.7" "0.15")
(command "_circle" "3517.944,936.7" "0.075")
(command "_circle" "3517.569,936.7" "0.075")
(command "_circle" "3517.194,936.7" "0.15")
(command "_circle" "3516.819,936.7" "0.075")
(command "_circle" "3516.444,936.7" "0.075")
(command "_circle" "3516.069,936.7" "0.15")
(command "_circle" "3515.694,936.7" "0.15")
(command "_circle" "3517.944,938.7" "0.075")
(command "_circle" "3517.569,938.7" "0.15")
(command "_circle" "3517.194,938.7" "0.15")
(command "_circle" "3516.819,938.7" "0.075")
(command "_circle" "3516.444,938.7" "0.075")
(command "_circle" "3516.069,938.7" "0.15")
(command "_circle" "3515.694,938.7" "0.15")
(command "_circle" "3517.944,940.7" "0.075")
(command "_circle" "3517.569,940.7" "0.075")
(command "_circle" "3517.194,940.7" "0.075")
(command "_circle" "3516.819,940.7" "0.15")
(command "_circle" "3516.444,940.7" "0.075")
(command "_circle" "3516.069,940.7" "0.15")
(command "_circle" "3515.694,940.7" "0.15")
(command "_circle" "3517.944,942.7" "0.075")
(command "_circle" "3517.569,942.7" "0.15")
(command "_circle" "3517.194,942.7" "0.075")
(command "_circle" "3516.819,942.7" "0.15")
(command "_circle" "3516.444,942.7" "0.075")
(command "_circle" "3516.069,942.7" "0.15")
(command "_circle" "3515.694,942.7" "0.15")
(command "_circle" "3517.944,944.7" "0.075")
(command "_circle" "3517.569,944.7" "0.075")
(command "_circle" "3517.194,944.7" "0.15")
(command "_circle" "3516.819,944.7" "0.15")
(command "_circle" "3516.444,944.7" "0.075")
(command "_circle" "3516.069,944.7" "0.15")
(command "_circle" "3515.694,944.7" "0.15")
(command "_circle" "3517.944,946.7" "0.075")
(command "_circle" "3517.569,946.7" "0.15")
(command "_circle" "3517.194,946.7" "0.15")
(command "_circle" "3516.819,946.7" "0.15")
(command "_circle" "3516.444,946.7" "0.075")
(command "_circle" "3516.069,946.7" "0.15")
(command "_circle" "3515.694,946.7" "0.15")
(command "_circle" "3517.944,948.7" "0.075")
(command "_circle" "3517.569,948.7" "0.075")
(command "_circle" "3517.194,948.7" "0.075")
(command "_circle" "3516.819,948.7" "0.075")
(command "_circle" "3516.444,948.7" "0.15")
(command "_circle" "3516.069,948.7" "0.15")
(command "_circle" "3515.694,948.7" "0.15")
(command "_circle" "3517.944,950.7" "0.075")
(command "_circle" "3517.569,950.7" "0.15")
(command "_circle" "3517.194,950.7" "0.075")
(command "_circle" "3516.819,950.7" "0.075")
(command "_circle" "3516.444,950.7" "0.15")
(command "_circle" "3516.069,950.7" "0.15")
(command "_circle" "3515.694,950.7" "0.15")
(command "_circle" "3517.944,952.7" "0.075")
(command "_circle" "3517.569,952.7" "0.075")
(command "_circle" "3517.194,952.7" "0.15")
(command "_circle" "3516.819,952.7" "0.075")
(command "_circle" "3516.444,952.7" "0.15")
(command "_circle" "3516.069,952.7" "0.15")
(command "_circle" "3515.694,952.7" "0.15")
(command "_circle" "3517.944,954.7" "0.075")
(command "_circle" "3517.569,954.7" "0.15")
(command "_circle" "3517.194,954.7" "0.15")
(command "_circle" "3516.819,954.7" "0.075")
(command "_circle" "3516.444,954.7" "0.15")
(command "_circle" "3516.069,954.7" "0.15")
(command "_circle" "3515.694,954.7" "0.15")
(command "_circle" "3517.944,956.7" "0.075")
(command "_circle" "3517.569,956.7" "0.075")
(command "_circle" "3517.194,956.7" "0.075")
(command "_circle" "3516.819,956.7" "0.15")
(command "_circle" "3516.444,956.7" "0.15")
(command "_circle" "3516.069,956.7" "0.15")
(command "_circle" "3515.694,956.7" "0.15")
(command "_circle" "3517.944,958.7" "0.075")
(command "_circle" "3517.569,958.7" "0.15")
(command "_circle" "3517.194,958.7" "0.075")
(command "_circle" "3516.819,958.7" "0.15")
(command "_circle" "3516.444,958.7" "0.15")
(command "_circle" "3516.069,958.7" "0.15")
(command "_circle" "3515.694,958.7" "0.15")
(command "_circle" "3517.944,960.7" "0.075")
(command "_circle" "3517.569,960.7" "0.075")
(command "_circle" "3517.194,960.7" "0.15")
(command "_circle" "3516.819,960.7" "0.15")
(command "_circle" "3516.444,960.7" "0.15")
(command "_circle" "3516.069,960.7" "0.15")
(command "_circle" "3515.694,960.7" "0.15")
(command "_circle" "3517.944,962.7" "0.075")
(command "_circle" "3517.569,962.7" "0.15")
(command "_circle" "3517.194,962.7" "0.15")
(command "_circle" "3516.819,962.7" "0.15")
(command "_circle" "3516.444,962.7" "0.15")
(command "_circle" "3516.069,962.7" "0.15")
(command "_circle" "3515.694,962.7" "0.15")
(command "_layer" "set" "nitride" "")
(command "_layer" "set" "text" "")
(command-s "_text" "3506.894,963.3" "2" "-90" "a = 370 nm" )
(sssetfirst nil (ssget "_L"))
(if (not (numberp (vl-string-search "Mac" (getvar "platform")))) (c:txtexp))
(command "_layer" "set" "nitride" "")
(command "_layer" "set" "text" "")
(command-s "_text" "3503.894,963.3" "2" "-90" "gap = 270 nm" )
(sssetfirst nil (ssget "_L"))
(if (not (numberp (vl-string-search "Mac" (getvar "platform")))) (c:txtexp))
(command "_layer" "set" "nitride" "")
(command "_layer" "set" "text" "")
(command-s "_text" "3500.894,963.3" "2" "-90" "amplitude = 132 nm" )
(sssetfirst nil (ssget "_L"))
(if (not (numberp (vl-string-search "Mac" (getvar "platform")))) (c:txtexp))
(command "_layer" "set" "nitride" "")
(command "_layer" "set" "text" "")
(command-s "_text" "3497.894,963.3" "2" "-90" "start width = 280 nm" )
(sssetfirst nil (ssget "_L"))
(if (not (numberp (vl-string-search "Mac" (getvar "platform")))) (c:txtexp))
(command "_layer" "set" "nitride" "")
(command "_layer" "set" "text" "")
(command-s "_text" "3494.894,963.3" "2" "-90" "width = 286 nm" )
(sssetfirst nil (ssget "_L"))
(if (not (numberp (vl-string-search "Mac" (getvar "platform")))) (c:txtexp))
(command "_layer" "set" "nitride" "")
(command "_layer" "set" "text" "")
(command-s "_text" "3491.894,963.3" "2" "-90" "taper: 15" )
(sssetfirst nil (ssget "_L"))
(if (not (numberp (vl-string-search "Mac" (getvar "platform")))) (c:txtexp))
(command "_layer" "set" "nitride" "")
(command "_layer" "set" "text" "")
(command-s "_text" "3488.894,963.3" "2" "-90" "nominal: 150" )
(sssetfirst nil (ssget "_L"))
(if (not (numberp (vl-string-search "Mac" (getvar "platform")))) (c:txtexp))
(command "_layer" "set" "nitride" "")
(command "_layer" "set" "indicators" "")
(setq coords (list 
(list 3440.415 940) 
(list 3440.415 920) 
(list 3420.415 900) 
(list 3440.415 880) 
(list 3440.415 860) 
(list 3440.415 900) 
(list 3440.415 887.0711) 
(list 3427.4861 900) 
(list 3440.415 912.9289) 
(list 3440.415 900)))
(apply 'command (append '("pline") coords '("c")))
(command "._fillet" "radius" "1" "._fillet" "P" (entlast))
(setq coords (list 
(list 3599.585 940) 
(list 3599.585 920) 
(list 3619.585 900) 
(list 3599.585 880) 
(list 3599.585 860) 
(list 3599.585 900) 
(list 3599.585 887.0711) 
(list 3612.5139 900) 
(list 3599.585 912.9289) 
(list 3599.585 900)))
(apply 'command (append '("pline") coords '("c")))
(command "._fillet" "radius" "1" "._fillet" "P" (entlast))
(command "_layer" "set" "holes" "")
(command "_circle" "3438.0629,914.1124" "0.5")
(command "_circle" "3435.7109,911.7603" "0.5")
(command "_circle" "3433.3588,909.4083" "0.5")
(command "_circle" "3431.0067,907.0562" "0.5")
(command "_circle" "3428.6547,904.7041" "0.5")
(command "_circle" "3426.3026,902.3521" "0.5")
(command "_circle" "3423.9505,900" "0.5")
(command "_circle" "3426.3026,897.6479" "0.5")
(command "_circle" "3428.6547,895.2959" "0.5")
(command "_circle" "3431.0067,892.9438" "0.5")
(command "_circle" "3433.3588,890.5917" "0.5")
(command "_circle" "3435.7109,888.2397" "0.5")
(command "_circle" "3438.0629,885.8876" "0.5")
(command "_circle" "3601.9371,914.1124" "0.5")
(command "_circle" "3604.2891,911.7603" "0.5")
(command "_circle" "3606.6412,909.4083" "0.5")
(command "_circle" "3608.9933,907.0562" "0.5")
(command "_circle" "3611.3453,904.7041" "0.5")
(command "_circle" "3613.6974,902.3521" "0.5")
(command "_circle" "3616.0495,900" "0.5")
(command "_circle" "3613.6974,897.6479" "0.5")
(command "_circle" "3611.3453,895.2959" "0.5")
(command "_circle" "3608.9933,892.9438" "0.5")
(command "_circle" "3606.6412,890.5917" "0.5")
(command "_circle" "3604.2891,888.2397" "0.5")
(command "_circle" "3601.9371,885.8876" "0.5")
(command "_layer" "set" "nitride" "")
(command "_block" "blkcoupler11" "3520,900" coupler11 "")
(command "_insert" "blkcoupler11" "3520,900" "1" "1" "0")
(command "_insert" "blkcoupler11" "3520,900" "1" "1" "180")
(command "_block" "blksinglenanobeam11" "3520,900" singlenanobeam11 "")
(command "_insert" "blksinglenanobeam11" "3520,900" "1" "1" "0")
(command "_insert" "blksinglenanobeam11" "3520,900" "1" "1" "180")
(command "_block" "blkanglednodearray11" "3520,900" anglednodearray11 "")
(command "_insert" "blkanglednodearray11" "3520,900" "1" "1" "0")
(command "_insert" "blkanglednodearray11" "3520,900" "1" "1" "180")
(command "_block" "blkcooledsinglenanobeam11" "3520,900" cooledsinglenanobeam11 "")
(command "_insert" "blkcooledsinglenanobeam11" "3520,900" "1" "1" "0")
(command "_insert" "blkcooledsinglenanobeam11" "3520,900" "1" "1" "180")
(command "_block" "blkyjunction11" "3520,900" yjunction11 "")
(command "_insert" "blkyjunction11" "3520,900" "1" "1" "0")
(command "_insert" "blkyjunction11" "3520,900" "1" "1" "180")
; DRAWING BULGING VEE GROOVE
(command "_layer" "set" "vgroove" "")
(setq coords (list 
(list 3445.415 -605) 
(list 3445.415 0) 
(list 3445.415 0) 
(list 3445.415 1800) 
(list 3445.415 1800) 
(list 3445.415 2405) 
(list 3594.585 2405) 
(list 3594.585 1800) 
(list 3594.585 1800) 
(list 3594.585 0) 
(list 3594.585 0) 
(list 3594.585 -605)))
(apply 'command (append '("pline") coords '("c")))
(command "._fillet" "radius" "0" "._fillet" "P" (entlast))
(command "_layer" "set" "window" "")
(command "_rectangle" "3445.415,-1935" "3594.585,-600")
(command "_rectangle" "3445.415,2400" "3594.585,5300")
(command "_layer" "set" "grid" "")
(command "_rectangle" "3446.415,-1934" "3469.9433,-1909.2133")
(command "_array" "last" "" "R" "75" "3" "25.7867" "24.5283")
(command "_rectangle" "3521,-1934" "3544.5283,-1909.2133")
(command "_array" "last" "" "R" "75" "3" "25.7867" "24.5283")
(command "_rectangle" "3446.415,1" "3469.9433,25.7")
(command "_array" "last" "" "R" "70" "3" "25.7" "24.5283")
(command "_rectangle" "3521,1" "3544.5283,25.7")
(command "_array" "last" "" "R" "70" "3" "25.7" "24.5283")
(command "_rectangle" "3446.415,1801" "3469.9433,1825.9185")
(command "_array" "last" "" "R" "135" "3" "25.9185" "24.5283")
(command "_rectangle" "3521,1801" "3544.5283,1825.9185")
(command "_array" "last" "" "R" "135" "3" "25.9185" "24.5283")
(command "_layer" "set" "vgrooveFDA" "")
(command "_rectangle" "3594.585,-2233" "3445.415,-1933")
(command "_layer" "set" "nitride" "")
(command "_layer" "set" "holes" "")
(command "_circle" "3597.085,331.5" "0.5")
(command "_array" "last" "" "R" "379" "1" "3" "2.5")
(command "_circle" "3442.915,331.5" "0.5")
(command "_array" "last" "" "R" "379" "1" "3" "-2.5")
(command "_layer" "set" "nitride" "")
(command "_layer" "set" "window" "")
(command "_layer" "set" "window" "")
(command "_rectangle" "3599.585,0" "3760.415,1800")
(command "._fillet" "radius" "20" "._fillet" "P" (entlast))
(command "_layer" "set" "grid" "")
(command "_rectangle" "3600.585,1" "3622.4179,25.7")
(command "_array" "last" "" "R" "70" "7" "25.7" "22.8329")
(command "_layer" "set" "nitride" "")
; DRAWING REGION LAYER
(command "_layer" "set" "regionLayer11" "")
(command "_rectangle" "3440,-460" "3600,2260")
(command "_layer" "set" "nitride" "")
(setq coupler11 nil)
(setq singlenanobeam11 nil)
(setq anglednodearray11 nil)
(setq cooledsinglenanobeam11 nil)
(setq yjunction11 nil)
; DEVICE #12
(command "_layer" "set" "window" "")
(command "_circle" "3752.915,-415" "5")
(command "_circle" "3752.915,-402.5" "5")
(command "_circle" "3752.915,-390" "5")
(command "_circle" "3752.915,-377.5" "5")
(command "_circle" "3740.415,-415" "5")
(command "_circle" "3740.415,-402.5" "5")
(command "_circle" "3740.415,-390" "5")
(command "_circle" "3740.415,-377.5" "5")
(command "_circle" "3727.915,-415" "5")
(command "_circle" "3727.915,-402.5" "5")
(command "_circle" "3727.915,-390" "5")
(command "_circle" "3727.915,-377.5" "5")
(command "_layer" "set" "nitride" "")
(setq currobj nil)
(setq currobj (ssadd))
; DRAWING COUPLER
(setq coords (list 
(list 3840.0655 -415) 
(list 3840.0655 -413) 
(list 3913.585 -413) 
(list 3913.585 -413) 
(list 3913.9677 -413.0761) 
(list 3914.2921 -413.2929) 
(list 3914.5089 -413.6173) 
(list 3914.585 -414) 
(list 3914.585 -411.8) 
(list 3914.585 -411.8) 
(list 3914.5089 -412.1827) 
(list 3914.2921 -412.5071) 
(list 3913.9677 -412.7239) 
(list 3913.585 -412.8) 
(list 3840.0655 -412.8) 
(list 3840.0655 -410.8) 
(list 3839.9345 -410.8) 
(list 3839.9345 -412.8) 
(list 3766.415 -412.8) 
(list 3766.0323 -412.7239) 
(list 3765.7079 -412.5071) 
(list 3765.4911 -412.1827) 
(list 3765.415 -411.8) 
(list 3765.415 -411.8) 
(list 3765.415 -414) 
(list 3765.4911 -413.6173) 
(list 3765.7079 -413.2929) 
(list 3766.0323 -413.0761) 
(list 3766.415 -413) 
(list 3766.415 -413) 
(list 3839.9345 -413) 
(list 3839.9345 -415)))
(apply 'command (append '("pline") coords '("c")))
(setq currobj (ssadd (entlast) currobj))
(command "._fillet" "radius" "0.3" "._fillet" "P" (entlast))
(command "_layer" "set" "holes" "")
(command "_circle" "3840,-412.9" "0.113")
(setq currobj (ssadd (entlast) currobj))
(command "_layer" "set" "nitride" "")
(command "_layer" "set" "text" "")
(command "_circle" "3839.2,-415" "0.075")
(command "_circle" "3839.2,-414.7" "0.075")
(command "_circle" "3839.2,-414.4" "0.075")
(command "_circle" "3838.9,-415" "0.075")
(command "_circle" "3838.9,-414.7" "0.075")
(command "_circle" "3838.9,-414.4" "0.075")
(command "_circle" "3838.6,-415" "0.075")
(command "_circle" "3838.6,-414.7" "0.075")
(command "_circle" "3838.6,-414.4" "0.075")
(command "_layer" "set" "nitride" "")
(command "_layer" "set" "prebias" "")
(command "_rectangle" "3765.415,-414" "3914.585,-411.8")
(setq currobj (ssadd (entlast) currobj))
(command "_rectangle" "3839.9345,-415" "3840.0655,-410.8")
(setq currobj (ssadd (entlast) currobj))
(command "_layer" "set" "nitride" "")
(setq coupler12 currobj)
(setq currobj nil)
(setq currobj (ssadd))
; DRAWING SINGLE NANOBEAM
(setq coords (list 
(list 3840.0655 -410.8) 
(list 3840.0655 -409.1417) 
(list 3840.0655 -407.4833) 
(list 3840.0655 -405.825) 
(list 3840.0655 -404.1667) 
(list 3840.0655 -402.5083) 
(list 3840.0655 -400.85) 
(list 3840.0655 -399.1917) 
(list 3840.0655 -397.5333) 
(list 3840.0655 -395.875) 
(list 3840.0656 -394.2167) 
(list 3840.0656 -392.5583) 
(list 3840.0656 -390.9) 
(list 3840.0657 -389.2417) 
(list 3840.0657 -387.5833) 
(list 3840.0657 -385.925) 
(list 3840.0658 -384.2667) 
(list 3840.0658 -382.6083) 
(list 3840.0659 -380.95) 
(list 3840.066 -379.2917) 
(list 3840.0661 -377.6333) 
(list 3840.0661 -375.975) 
(list 3840.0662 -374.3167) 
(list 3840.0663 -372.6583) 
(list 3840.0665 -371) 
(list 3840.0666 -369.3417) 
(list 3840.0667 -367.6833) 
(list 3840.0669 -366.025) 
(list 3840.067 -364.3667) 
(list 3840.0672 -362.7083) 
(list 3840.0674 -361.05) 
(list 3840.0676 -359.3917) 
(list 3840.0678 -357.7333) 
(list 3840.068 -356.075) 
(list 3840.0682 -354.4167) 
(list 3840.0685 -352.7583) 
(list 3840.0687 -351.1) 
(list 3840.069 -349.4417) 
(list 3840.0693 -347.7833) 
(list 3840.0696 -346.125) 
(list 3840.0699 -344.4667) 
(list 3840.0703 -342.8083) 
(list 3840.0706 -341.15) 
(list 3840.071 -339.4917) 
(list 3840.0714 -337.8333) 
(list 3840.0718 -336.175) 
(list 3840.0722 -334.5167) 
(list 3840.0727 -332.8583) 
(list 3840.0731 -331.2) 
(list 3840.0736 -329.5417) 
(list 3840.0741 -327.8833) 
(list 3840.0747 -326.225) 
(list 3840.0752 -324.5667) 
(list 3840.0758 -322.9083) 
(list 3840.0764 -321.25) 
(list 3840.077 -319.5917) 
(list 3840.0776 -317.9333) 
(list 3840.0783 -316.275) 
(list 3840.079 -314.6167) 
(list 3840.0797 -312.9583) 
(list 3840.0804 -311.3) 
(list 3840.0812 -309.6417) 
(list 3840.082 -307.9833) 
(list 3840.0828 -306.325) 
(list 3840.0836 -304.6667) 
(list 3840.0845 -303.0083) 
(list 3840.0854 -301.35) 
(list 3840.0863 -299.6917) 
(list 3840.0872 -298.0333) 
(list 3840.0882 -296.375) 
(list 3840.0892 -294.7167) 
(list 3840.0903 -293.0583) 
(list 3840.0913 -291.4) 
(list 3840.0924 -289.7417) 
(list 3840.0935 -288.0833) 
(list 3840.0947 -286.425) 
(list 3840.0959 -284.7667) 
(list 3840.0971 -283.1083) 
(list 3840.0983 -281.45) 
(list 3840.0996 -279.7917) 
(list 3840.1009 -278.1333) 
(list 3840.1023 -276.475) 
(list 3840.1036 -274.8167) 
(list 3840.105 -273.1583) 
(list 3840.1065 -271.5) 
(list 3840.108 -269.8417) 
(list 3840.1095 -268.1833) 
(list 3840.111 -266.525) 
(list 3840.1126 -264.8667) 
(list 3840.1143 -263.2083) 
(list 3840.1159 -261.55) 
(list 3840.1176 -259.8917) 
(list 3840.1193 -258.2333) 
(list 3840.1211 -256.575) 
(list 3840.1229 -254.9167) 
(list 3840.1248 -253.2583) 
(list 3840.1267 -251.6) 
(list 3840.1286 -249.9417) 
(list 3840.1306 -248.2833) 
(list 3840.1326 -246.625) 
(list 3840.1347 -244.9667) 
(list 3840.1368 -243.3083) 
(list 3840.1389 -241.65) 
(list 3840.1411 -239.9917) 
(list 3840.1433 -238.3333) 
(list 3840.1456 -236.675) 
(list 3840.1479 -235.0167) 
(list 3840.1502 -233.3583) 
(list 3840.1526 -231.7) 
(list 3840.1551 -230.0417) 
(list 3840.1575 -228.3833) 
(list 3840.1601 -226.725) 
(list 3840.1627 -225.0667) 
(list 3840.1653 -223.4083) 
(list 3840.168 -221.75) 
(list 3840.1707 -220.0917) 
(list 3840.1734 -218.4333) 
(list 3840.1763 -216.775) 
(list 3840.1791 -215.1167) 
(list 3840.182 -213.4583) 
(list 3840.185 -211.8) 
(list 3839.815 -211.8) 
(list 3839.818 -213.4583) 
(list 3839.8209 -215.1167) 
(list 3839.8237 -216.775) 
(list 3839.8266 -218.4333) 
(list 3839.8293 -220.0917) 
(list 3839.832 -221.75) 
(list 3839.8347 -223.4083) 
(list 3839.8373 -225.0667) 
(list 3839.8399 -226.725) 
(list 3839.8425 -228.3833) 
(list 3839.8449 -230.0417) 
(list 3839.8474 -231.7) 
(list 3839.8498 -233.3583) 
(list 3839.8521 -235.0167) 
(list 3839.8544 -236.675) 
(list 3839.8567 -238.3333) 
(list 3839.8589 -239.9917) 
(list 3839.8611 -241.65) 
(list 3839.8632 -243.3083) 
(list 3839.8653 -244.9667) 
(list 3839.8674 -246.625) 
(list 3839.8694 -248.2833) 
(list 3839.8714 -249.9417) 
(list 3839.8733 -251.6) 
(list 3839.8752 -253.2583) 
(list 3839.8771 -254.9167) 
(list 3839.8789 -256.575) 
(list 3839.8807 -258.2333) 
(list 3839.8824 -259.8917) 
(list 3839.8841 -261.55) 
(list 3839.8857 -263.2083) 
(list 3839.8874 -264.8667) 
(list 3839.889 -266.525) 
(list 3839.8905 -268.1833) 
(list 3839.892 -269.8417) 
(list 3839.8935 -271.5) 
(list 3839.895 -273.1583) 
(list 3839.8964 -274.8167) 
(list 3839.8977 -276.475) 
(list 3839.8991 -278.1333) 
(list 3839.9004 -279.7917) 
(list 3839.9017 -281.45) 
(list 3839.9029 -283.1083) 
(list 3839.9041 -284.7667) 
(list 3839.9053 -286.425) 
(list 3839.9065 -288.0833) 
(list 3839.9076 -289.7417) 
(list 3839.9087 -291.4) 
(list 3839.9097 -293.0583) 
(list 3839.9108 -294.7167) 
(list 3839.9118 -296.375) 
(list 3839.9128 -298.0333) 
(list 3839.9137 -299.6917) 
(list 3839.9146 -301.35) 
(list 3839.9155 -303.0083) 
(list 3839.9164 -304.6667) 
(list 3839.9172 -306.325) 
(list 3839.918 -307.9833) 
(list 3839.9188 -309.6417) 
(list 3839.9196 -311.3) 
(list 3839.9203 -312.9583) 
(list 3839.921 -314.6167) 
(list 3839.9217 -316.275) 
(list 3839.9224 -317.9333) 
(list 3839.923 -319.5917) 
(list 3839.9236 -321.25) 
(list 3839.9242 -322.9083) 
(list 3839.9248 -324.5667) 
(list 3839.9253 -326.225) 
(list 3839.9259 -327.8833) 
(list 3839.9264 -329.5417) 
(list 3839.9269 -331.2) 
(list 3839.9273 -332.8583) 
(list 3839.9278 -334.5167) 
(list 3839.9282 -336.175) 
(list 3839.9286 -337.8333) 
(list 3839.929 -339.4917) 
(list 3839.9294 -341.15) 
(list 3839.9297 -342.8083) 
(list 3839.9301 -344.4667) 
(list 3839.9304 -346.125) 
(list 3839.9307 -347.7833) 
(list 3839.931 -349.4417) 
(list 3839.9313 -351.1) 
(list 3839.9315 -352.7583) 
(list 3839.9318 -354.4167) 
(list 3839.932 -356.075) 
(list 3839.9322 -357.7333) 
(list 3839.9324 -359.3917) 
(list 3839.9326 -361.05) 
(list 3839.9328 -362.7083) 
(list 3839.933 -364.3667) 
(list 3839.9331 -366.025) 
(list 3839.9333 -367.6833) 
(list 3839.9334 -369.3417) 
(list 3839.9335 -371) 
(list 3839.9337 -372.6583) 
(list 3839.9338 -374.3167) 
(list 3839.9339 -375.975) 
(list 3839.9339 -377.6333) 
(list 3839.934 -379.2917) 
(list 3839.9341 -380.95) 
(list 3839.9342 -382.6083) 
(list 3839.9342 -384.2667) 
(list 3839.9343 -385.925) 
(list 3839.9343 -387.5833) 
(list 3839.9343 -389.2417) 
(list 3839.9344 -390.9) 
(list 3839.9344 -392.5583) 
(list 3839.9344 -394.2167) 
(list 3839.9345 -395.875) 
(list 3839.9345 -397.5333) 
(list 3839.9345 -399.1917) 
(list 3839.9345 -400.85) 
(list 3839.9345 -402.5083) 
(list 3839.9345 -404.1667) 
(list 3839.9345 -405.825) 
(list 3839.9345 -407.4833) 
(list 3839.9345 -409.1417) 
(list 3839.9345 -410.8)))
(apply 'command (append '("pline") coords '("c")))
(setq currobj (ssadd (entlast) currobj))
(command "_layer" "set" "prebias" "")
(command "_rectangle" "3839.815,-410.8" "3840.185,-211.8")
(setq currobj (ssadd (entlast) currobj))
(command "_layer" "set" "nitride" "")
(setq singlenanobeam12 currobj)
(setq currobj nil)
(setq currobj (ssadd))
; DRAWING NODE ARRAY
(setq coords (list 
(list 3840.185 -211.8) 
(list 3840.5625 -201.8) 
(list 3840.5625 -201.8) 
(list 3840.5625 -200.8) 
(list 3914.585 -212.6864) 
(list 3914.585 -207.7434) 
(list 3840.5625 -197.357) 
(list 3840.5625 -196.357) 
(list 3840.5625 -196.357) 
(list 3840.2625 -186.357) 
(list 3839.7375 -186.357) 
(list 3839.4375 -196.357) 
(list 3839.4375 -196.357) 
(list 3839.4375 -197.357) 
(list 3765.415 -207.7434) 
(list 3765.415 -212.6864) 
(list 3839.4375 -200.8) 
(list 3839.4375 -201.8) 
(list 3839.4375 -201.8) 
(list 3839.815 -211.8)))
(apply 'command (append '("pline") coords '("c")))
(setq currobj (ssadd (entlast) currobj))
(command "_layer" "set" "prebias" "")
(setq coords (list 
(list 3839.4375 -212.6864) 
(list 3839.4375 -200.8) 
(list 3765.415 -212.6864) 
(list 3765.415 -207.7434) 
(list 3839.4375 -197.357) 
(list 3839.4375 -186.357) 
(list 3840.5625 -186.357) 
(list 3840.5625 -197.357) 
(list 3914.585 -207.7434) 
(list 3914.585 -212.6864) 
(list 3840.5625 -200.8) 
(list 3840.5625 -212.6864)))
(apply 'command (append '("pline") coords '("c")))
(setq currobj (ssadd (entlast) currobj))
(command "_layer" "set" "nitride" "")
(command "_layer" "set" "fda1" "")
(setq coords (list 
(list 3840.5625 -200.657) 
(list 3914.585 -212.5434) 
(list 3914.585 -212.3664) 
(list 3840.5625 -200.58)))
(apply 'command (append '("pline") coords '("c")))
(setq currobj (ssadd (entlast) currobj))
(setq coords (list 
(list 3840.5625 -200.437) 
(list 3914.585 -212.2234) 
(list 3914.585 -212.0464) 
(list 3840.5625 -200.36)))
(apply 'command (append '("pline") coords '("c")))
(setq currobj (ssadd (entlast) currobj))
(setq coords (list 
(list 3840.5625 -200.217) 
(list 3914.585 -211.9034) 
(list 3914.585 -211.7264) 
(list 3840.5625 -200.14)))
(apply 'command (append '("pline") coords '("c")))
(setq currobj (ssadd (entlast) currobj))
(setq coords (list 
(list 3840.5625 -199.997) 
(list 3914.585 -211.5834) 
(list 3914.585 -211.4064) 
(list 3840.5625 -199.92)))
(apply 'command (append '("pline") coords '("c")))
(setq currobj (ssadd (entlast) currobj))
(setq coords (list 
(list 3840.5625 -199.777) 
(list 3914.585 -211.2634) 
(list 3914.585 -211.0864) 
(list 3840.5625 -199.7)))
(apply 'command (append '("pline") coords '("c")))
(setq currobj (ssadd (entlast) currobj))
(setq coords (list 
(list 3840.5625 -199.557) 
(list 3914.585 -210.9434) 
(list 3914.585 -210.7664) 
(list 3840.5625 -199.48)))
(apply 'command (append '("pline") coords '("c")))
(setq currobj (ssadd (entlast) currobj))
(setq coords (list 
(list 3840.5625 -199.337) 
(list 3914.585 -210.6234) 
(list 3914.585 -210.4464) 
(list 3840.5625 -199.26)))
(apply 'command (append '("pline") coords '("c")))
(setq currobj (ssadd (entlast) currobj))
(setq coords (list 
(list 3840.5625 -199.117) 
(list 3914.585 -210.3034) 
(list 3914.585 -210.1264) 
(list 3840.5625 -199.04)))
(apply 'command (append '("pline") coords '("c")))
(setq currobj (ssadd (entlast) currobj))
(setq coords (list 
(list 3840.5625 -198.897) 
(list 3914.585 -209.9834) 
(list 3914.585 -209.8064) 
(list 3840.5625 -198.82)))
(apply 'command (append '("pline") coords '("c")))
(setq currobj (ssadd (entlast) currobj))
(setq coords (list 
(list 3840.5625 -198.677) 
(list 3914.585 -209.6634) 
(list 3914.585 -209.4864) 
(list 3840.5625 -198.6)))
(apply 'command (append '("pline") coords '("c")))
(setq currobj (ssadd (entlast) currobj))
(setq coords (list 
(list 3840.5625 -198.457) 
(list 3914.585 -209.3434) 
(list 3914.585 -209.1664) 
(list 3840.5625 -198.38)))
(apply 'command (append '("pline") coords '("c")))
(setq currobj (ssadd (entlast) currobj))
(setq coords (list 
(list 3840.5625 -198.237) 
(list 3914.585 -209.0234) 
(list 3914.585 -208.8464) 
(list 3840.5625 -198.16)))
(apply 'command (append '("pline") coords '("c")))
(setq currobj (ssadd (entlast) currobj))
(setq coords (list 
(list 3840.5625 -198.017) 
(list 3914.585 -208.7034) 
(list 3914.585 -208.5264) 
(list 3840.5625 -197.94)))
(apply 'command (append '("pline") coords '("c")))
(setq currobj (ssadd (entlast) currobj))
(setq coords (list 
(list 3840.5625 -197.797) 
(list 3914.585 -208.3834) 
(list 3914.585 -208.2064) 
(list 3840.5625 -197.72)))
(apply 'command (append '("pline") coords '("c")))
(setq currobj (ssadd (entlast) currobj))
(setq coords (list 
(list 3840.5625 -197.577) 
(list 3914.585 -208.0634) 
(list 3914.585 -207.8864) 
(list 3840.5625 -197.5)))
(apply 'command (append '("pline") coords '("c")))
(setq currobj (ssadd (entlast) currobj))
(setq coords (list 
(list 3839.4375 -197.5) 
(list 3765.415 -207.8864) 
(list 3765.415 -208.0634) 
(list 3839.4375 -197.577)))
(apply 'command (append '("pline") coords '("c")))
(setq currobj (ssadd (entlast) currobj))
(setq coords (list 
(list 3839.4375 -197.72) 
(list 3765.415 -208.2064) 
(list 3765.415 -208.3834) 
(list 3839.4375 -197.797)))
(apply 'command (append '("pline") coords '("c")))
(setq currobj (ssadd (entlast) currobj))
(setq coords (list 
(list 3839.4375 -197.94) 
(list 3765.415 -208.5264) 
(list 3765.415 -208.7034) 
(list 3839.4375 -198.017)))
(apply 'command (append '("pline") coords '("c")))
(setq currobj (ssadd (entlast) currobj))
(setq coords (list 
(list 3839.4375 -198.16) 
(list 3765.415 -208.8464) 
(list 3765.415 -209.0234) 
(list 3839.4375 -198.237)))
(apply 'command (append '("pline") coords '("c")))
(setq currobj (ssadd (entlast) currobj))
(setq coords (list 
(list 3839.4375 -198.38) 
(list 3765.415 -209.1664) 
(list 3765.415 -209.3434) 
(list 3839.4375 -198.457)))
(apply 'command (append '("pline") coords '("c")))
(setq currobj (ssadd (entlast) currobj))
(setq coords (list 
(list 3839.4375 -198.6) 
(list 3765.415 -209.4864) 
(list 3765.415 -209.6634) 
(list 3839.4375 -198.677)))
(apply 'command (append '("pline") coords '("c")))
(setq currobj (ssadd (entlast) currobj))
(setq coords (list 
(list 3839.4375 -198.82) 
(list 3765.415 -209.8064) 
(list 3765.415 -209.9834) 
(list 3839.4375 -198.897)))
(apply 'command (append '("pline") coords '("c")))
(setq currobj (ssadd (entlast) currobj))
(setq coords (list 
(list 3839.4375 -199.04) 
(list 3765.415 -210.1264) 
(list 3765.415 -210.3034) 
(list 3839.4375 -199.117)))
(apply 'command (append '("pline") coords '("c")))
(setq currobj (ssadd (entlast) currobj))
(setq coords (list 
(list 3839.4375 -199.26) 
(list 3765.415 -210.4464) 
(list 3765.415 -210.6234) 
(list 3839.4375 -199.337)))
(apply 'command (append '("pline") coords '("c")))
(setq currobj (ssadd (entlast) currobj))
(setq coords (list 
(list 3839.4375 -199.48) 
(list 3765.415 -210.7664) 
(list 3765.415 -210.9434) 
(list 3839.4375 -199.557)))
(apply 'command (append '("pline") coords '("c")))
(setq currobj (ssadd (entlast) currobj))
(setq coords (list 
(list 3839.4375 -199.7) 
(list 3765.415 -211.0864) 
(list 3765.415 -211.2634) 
(list 3839.4375 -199.777)))
(apply 'command (append '("pline") coords '("c")))
(setq currobj (ssadd (entlast) currobj))
(setq coords (list 
(list 3839.4375 -199.92) 
(list 3765.415 -211.4064) 
(list 3765.415 -211.5834) 
(list 3839.4375 -199.997)))
(apply 'command (append '("pline") coords '("c")))
(setq currobj (ssadd (entlast) currobj))
(setq coords (list 
(list 3839.4375 -200.14) 
(list 3765.415 -211.7264) 
(list 3765.415 -211.9034) 
(list 3839.4375 -200.217)))
(apply 'command (append '("pline") coords '("c")))
(setq currobj (ssadd (entlast) currobj))
(setq coords (list 
(list 3839.4375 -200.36) 
(list 3765.415 -212.0464) 
(list 3765.415 -212.2234) 
(list 3839.4375 -200.437)))
(apply 'command (append '("pline") coords '("c")))
(setq currobj (ssadd (entlast) currobj))
(setq coords (list 
(list 3839.4375 -200.58) 
(list 3765.415 -212.3664) 
(list 3765.415 -212.5434) 
(list 3839.4375 -200.657)))
(apply 'command (append '("pline") coords '("c")))
(setq currobj (ssadd (entlast) currobj))
(command "_layer" "set" "nitride" "")
(command "_layer" "set" "text" "")
(command "_circle" "3838.985,-211.8" "0.075")
(command "_circle" "3838.985,-211.5" "0.075")
(command "_circle" "3838.985,-211.2" "0.075")
(command "_circle" "3838.985,-210.9" "0.075")
(command "_circle" "3838.985,-210.6" "0.075")
(command "_circle" "3838.685,-211.8" "0.075")
(command "_circle" "3838.685,-211.5" "0.075")
(command "_circle" "3838.685,-211.2" "0.075")
(command "_circle" "3838.685,-210.9" "0.075")
(command "_circle" "3838.685,-210.6" "0.075")
(command "_circle" "3838.385,-211.8" "0.075")
(command "_circle" "3838.385,-211.5" "0.075")
(command "_circle" "3838.385,-211.2" "0.075")
(command "_circle" "3838.385,-210.9" "0.075")
(command "_circle" "3838.385,-210.6" "0.075")
(command "_circle" "3838.085,-211.8" "0.075")
(command "_circle" "3838.085,-211.5" "0.075")
(command "_circle" "3838.085,-211.2" "0.075")
(command "_circle" "3838.085,-210.9" "0.075")
(command "_circle" "3838.085,-210.6" "0.075")
(command "_circle" "3837.785,-211.8" "0.075")
(command "_circle" "3837.785,-211.5" "0.075")
(command "_circle" "3837.785,-211.2" "0.075")
(command "_circle" "3837.785,-210.9" "0.075")
(command "_circle" "3837.785,-210.6" "0.075")
(command "_layer" "set" "nitride" "")
(setq anglednodearray12 currobj)
(setq currobj nil)
(setq currobj (ssadd))
; DRAWING COOLED SINGLE NANOBEAM
(setq coords (list 
(list 3840.2625 -186.357) 
(list 3840.2625 -181.357) 
(list 3839.7375 -181.357) 
(list 3839.7375 -186.357)))
(apply 'command (append '("pline") coords '("c")))
(setq currobj (ssadd (entlast) currobj))
(command "_layer" "set" "prebias" "")
(command "_rectangle" "3839.7375,-186.357" "3840.2625,-181.357")
(setq currobj (ssadd (entlast) currobj))
(command "_layer" "set" "nitride" "")
(setq coords (list 
(list 3840.2625 -181.357) 
(list 3840.5625 -171.357) 
(list 3840.5625 -171.357) 
(list 3840.5625 -170.357) 
(list 3914.585 -171.107) 
(list 3914.585 -166.164) 
(list 3840.5625 -166.914) 
(list 3840.5625 -165.914) 
(list 3840.5625 -165.914) 
(list 3840.2625 -155.914) 
(list 3839.7375 -155.914) 
(list 3839.4375 -165.914) 
(list 3839.4375 -165.914) 
(list 3839.4375 -166.914) 
(list 3765.415 -166.164) 
(list 3765.415 -171.107) 
(list 3839.4375 -170.357) 
(list 3839.4375 -171.357) 
(list 3839.4375 -171.357) 
(list 3839.7375 -181.357)))
(apply 'command (append '("pline") coords '("c")))
(setq currobj (ssadd (entlast) currobj))
(command "_layer" "set" "prebias" "")
(setq coords (list 
(list 3839.4375 -181.357) 
(list 3839.4375 -170.357) 
(list 3765.415 -171.107) 
(list 3765.415 -166.164) 
(list 3839.4375 -166.914) 
(list 3839.4375 -155.914) 
(list 3840.5625 -155.914) 
(list 3840.5625 -166.914) 
(list 3914.585 -166.164) 
(list 3914.585 -171.107) 
(list 3840.5625 -170.357) 
(list 3840.5625 -181.357)))
(apply 'command (append '("pline") coords '("c")))
(setq currobj (ssadd (entlast) currobj))
(command "_layer" "set" "nitride" "")
(command "_layer" "set" "fda1" "")
(setq coords (list 
(list 3840.5625 -170.214) 
(list 3914.585 -170.964) 
(list 3914.585 -170.787) 
(list 3840.5625 -170.137)))
(apply 'command (append '("pline") coords '("c")))
(setq currobj (ssadd (entlast) currobj))
(setq coords (list 
(list 3840.5625 -169.994) 
(list 3914.585 -170.644) 
(list 3914.585 -170.467) 
(list 3840.5625 -169.917)))
(apply 'command (append '("pline") coords '("c")))
(setq currobj (ssadd (entlast) currobj))
(setq coords (list 
(list 3840.5625 -169.774) 
(list 3914.585 -170.324) 
(list 3914.585 -170.147) 
(list 3840.5625 -169.697)))
(apply 'command (append '("pline") coords '("c")))
(setq currobj (ssadd (entlast) currobj))
(setq coords (list 
(list 3840.5625 -169.554) 
(list 3914.585 -170.004) 
(list 3914.585 -169.827) 
(list 3840.5625 -169.477)))
(apply 'command (append '("pline") coords '("c")))
(setq currobj (ssadd (entlast) currobj))
(setq coords (list 
(list 3840.5625 -169.334) 
(list 3914.585 -169.684) 
(list 3914.585 -169.507) 
(list 3840.5625 -169.257)))
(apply 'command (append '("pline") coords '("c")))
(setq currobj (ssadd (entlast) currobj))
(setq coords (list 
(list 3840.5625 -169.114) 
(list 3914.585 -169.364) 
(list 3914.585 -169.187) 
(list 3840.5625 -169.037)))
(apply 'command (append '("pline") coords '("c")))
(setq currobj (ssadd (entlast) currobj))
(setq coords (list 
(list 3840.5625 -168.894) 
(list 3914.585 -169.044) 
(list 3914.585 -168.867) 
(list 3840.5625 -168.817)))
(apply 'command (append '("pline") coords '("c")))
(setq currobj (ssadd (entlast) currobj))
(setq coords (list 
(list 3840.5625 -168.674) 
(list 3914.585 -168.724) 
(list 3914.585 -168.547) 
(list 3840.5625 -168.597)))
(apply 'command (append '("pline") coords '("c")))
(setq currobj (ssadd (entlast) currobj))
(setq coords (list 
(list 3840.5625 -168.454) 
(list 3914.585 -168.404) 
(list 3914.585 -168.227) 
(list 3840.5625 -168.377)))
(apply 'command (append '("pline") coords '("c")))
(setq currobj (ssadd (entlast) currobj))
(setq coords (list 
(list 3840.5625 -168.234) 
(list 3914.585 -168.084) 
(list 3914.585 -167.907) 
(list 3840.5625 -168.157)))
(apply 'command (append '("pline") coords '("c")))
(setq currobj (ssadd (entlast) currobj))
(setq coords (list 
(list 3840.5625 -168.014) 
(list 3914.585 -167.764) 
(list 3914.585 -167.587) 
(list 3840.5625 -167.937)))
(apply 'command (append '("pline") coords '("c")))
(setq currobj (ssadd (entlast) currobj))
(setq coords (list 
(list 3840.5625 -167.794) 
(list 3914.585 -167.444) 
(list 3914.585 -167.267) 
(list 3840.5625 -167.717)))
(apply 'command (append '("pline") coords '("c")))
(setq currobj (ssadd (entlast) currobj))
(setq coords (list 
(list 3840.5625 -167.574) 
(list 3914.585 -167.124) 
(list 3914.585 -166.947) 
(list 3840.5625 -167.497)))
(apply 'command (append '("pline") coords '("c")))
(setq currobj (ssadd (entlast) currobj))
(setq coords (list 
(list 3840.5625 -167.354) 
(list 3914.585 -166.804) 
(list 3914.585 -166.627) 
(list 3840.5625 -167.277)))
(apply 'command (append '("pline") coords '("c")))
(setq currobj (ssadd (entlast) currobj))
(setq coords (list 
(list 3840.5625 -167.134) 
(list 3914.585 -166.484) 
(list 3914.585 -166.307) 
(list 3840.5625 -167.057)))
(apply 'command (append '("pline") coords '("c")))
(setq currobj (ssadd (entlast) currobj))
(setq coords (list 
(list 3839.4375 -167.057) 
(list 3765.415 -166.307) 
(list 3765.415 -166.484) 
(list 3839.4375 -167.134)))
(apply 'command (append '("pline") coords '("c")))
(setq currobj (ssadd (entlast) currobj))
(setq coords (list 
(list 3839.4375 -167.277) 
(list 3765.415 -166.627) 
(list 3765.415 -166.804) 
(list 3839.4375 -167.354)))
(apply 'command (append '("pline") coords '("c")))
(setq currobj (ssadd (entlast) currobj))
(setq coords (list 
(list 3839.4375 -167.497) 
(list 3765.415 -166.947) 
(list 3765.415 -167.124) 
(list 3839.4375 -167.574)))
(apply 'command (append '("pline") coords '("c")))
(setq currobj (ssadd (entlast) currobj))
(setq coords (list 
(list 3839.4375 -167.717) 
(list 3765.415 -167.267) 
(list 3765.415 -167.444) 
(list 3839.4375 -167.794)))
(apply 'command (append '("pline") coords '("c")))
(setq currobj (ssadd (entlast) currobj))
(setq coords (list 
(list 3839.4375 -167.937) 
(list 3765.415 -167.587) 
(list 3765.415 -167.764) 
(list 3839.4375 -168.014)))
(apply 'command (append '("pline") coords '("c")))
(setq currobj (ssadd (entlast) currobj))
(setq coords (list 
(list 3839.4375 -168.157) 
(list 3765.415 -167.907) 
(list 3765.415 -168.084) 
(list 3839.4375 -168.234)))
(apply 'command (append '("pline") coords '("c")))
(setq currobj (ssadd (entlast) currobj))
(setq coords (list 
(list 3839.4375 -168.377) 
(list 3765.415 -168.227) 
(list 3765.415 -168.404) 
(list 3839.4375 -168.454)))
(apply 'command (append '("pline") coords '("c")))
(setq currobj (ssadd (entlast) currobj))
(setq coords (list 
(list 3839.4375 -168.597) 
(list 3765.415 -168.547) 
(list 3765.415 -168.724) 
(list 3839.4375 -168.674)))
(apply 'command (append '("pline") coords '("c")))
(setq currobj (ssadd (entlast) currobj))
(setq coords (list 
(list 3839.4375 -168.817) 
(list 3765.415 -168.867) 
(list 3765.415 -169.044) 
(list 3839.4375 -168.894)))
(apply 'command (append '("pline") coords '("c")))
(setq currobj (ssadd (entlast) currobj))
(setq coords (list 
(list 3839.4375 -169.037) 
(list 3765.415 -169.187) 
(list 3765.415 -169.364) 
(list 3839.4375 -169.114)))
(apply 'command (append '("pline") coords '("c")))
(setq currobj (ssadd (entlast) currobj))
(setq coords (list 
(list 3839.4375 -169.257) 
(list 3765.415 -169.507) 
(list 3765.415 -169.684) 
(list 3839.4375 -169.334)))
(apply 'command (append '("pline") coords '("c")))
(setq currobj (ssadd (entlast) currobj))
(setq coords (list 
(list 3839.4375 -169.477) 
(list 3765.415 -169.827) 
(list 3765.415 -170.004) 
(list 3839.4375 -169.554)))
(apply 'command (append '("pline") coords '("c")))
(setq currobj (ssadd (entlast) currobj))
(setq coords (list 
(list 3839.4375 -169.697) 
(list 3765.415 -170.147) 
(list 3765.415 -170.324) 
(list 3839.4375 -169.774)))
(apply 'command (append '("pline") coords '("c")))
(setq currobj (ssadd (entlast) currobj))
(setq coords (list 
(list 3839.4375 -169.917) 
(list 3765.415 -170.467) 
(list 3765.415 -170.644) 
(list 3839.4375 -169.994)))
(apply 'command (append '("pline") coords '("c")))
(setq currobj (ssadd (entlast) currobj))
(setq coords (list 
(list 3839.4375 -170.137) 
(list 3765.415 -170.787) 
(list 3765.415 -170.964) 
(list 3839.4375 -170.214)))
(apply 'command (append '("pline") coords '("c")))
(setq currobj (ssadd (entlast) currobj))
(command "_layer" "set" "nitride" "")
(command "_layer" "set" "text" "")
(command "_circle" "3839.0625,-181.357" "0.075")
(command "_circle" "3839.0625,-181.057" "0.075")
(command "_circle" "3839.0625,-180.757" "0.075")
(command "_circle" "3839.0625,-180.457" "0.075")
(command "_circle" "3839.0625,-180.157" "0.075")
(command "_circle" "3838.7625,-181.357" "0.075")
(command "_circle" "3838.7625,-181.057" "0.075")
(command "_circle" "3838.7625,-180.757" "0.075")
(command "_circle" "3838.7625,-180.457" "0.075")
(command "_circle" "3838.7625,-180.157" "0.075")
(command "_circle" "3838.4625,-181.357" "0.075")
(command "_circle" "3838.4625,-181.057" "0.075")
(command "_circle" "3838.4625,-180.757" "0.075")
(command "_circle" "3838.4625,-180.457" "0.075")
(command "_circle" "3838.4625,-180.157" "0.075")
(command "_circle" "3838.1625,-181.357" "0.075")
(command "_circle" "3838.1625,-181.057" "0.075")
(command "_circle" "3838.1625,-180.757" "0.075")
(command "_circle" "3838.1625,-180.457" "0.075")
(command "_circle" "3838.1625,-180.157" "0.075")
(command "_circle" "3837.8625,-181.357" "0.075")
(command "_circle" "3837.8625,-181.057" "0.075")
(command "_circle" "3837.8625,-180.757" "0.075")
(command "_circle" "3837.8625,-180.457" "0.075")
(command "_circle" "3837.8625,-180.157" "0.075")
(command "_layer" "set" "nitride" "")
(setq coords (list 
(list 3840.2625 -155.914) 
(list 3840.2625 -40.2693) 
(list 3839.7375 -40.2693) 
(list 3839.7375 -155.914)))
(apply 'command (append '("pline") coords '("c")))
(setq currobj (ssadd (entlast) currobj))
(command "_layer" "set" "prebias" "")
(command "_rectangle" "3839.7375,-155.914" "3840.2625,-40.2693")
(setq currobj (ssadd (entlast) currobj))
(command "_layer" "set" "nitride" "")
(setq coords (list 
(list 3840.2625 -40.2693) 
(list 3840.5625 -30.2693) 
(list 3840.5625 -30.2693) 
(list 3840.5625 -29.2693) 
(list 3914.585 -30.0193) 
(list 3914.585 -25.0763) 
(list 3840.5625 -25.8263) 
(list 3840.5625 -24.8263) 
(list 3840.5625 -24.8263) 
(list 3840.2625 -14.8263) 
(list 3839.7375 -14.8263) 
(list 3839.4375 -24.8263) 
(list 3839.4375 -24.8263) 
(list 3839.4375 -25.8263) 
(list 3765.415 -25.0763) 
(list 3765.415 -30.0193) 
(list 3839.4375 -29.2693) 
(list 3839.4375 -30.2693) 
(list 3839.4375 -30.2693) 
(list 3839.7375 -40.2693)))
(apply 'command (append '("pline") coords '("c")))
(setq currobj (ssadd (entlast) currobj))
(command "_layer" "set" "prebias" "")
(setq coords (list 
(list 3839.4375 -40.2693) 
(list 3839.4375 -29.2693) 
(list 3765.415 -30.0193) 
(list 3765.415 -25.0763) 
(list 3839.4375 -25.8263) 
(list 3839.4375 -14.8263) 
(list 3840.5625 -14.8263) 
(list 3840.5625 -25.8263) 
(list 3914.585 -25.0763) 
(list 3914.585 -30.0193) 
(list 3840.5625 -29.2693) 
(list 3840.5625 -40.2693)))
(apply 'command (append '("pline") coords '("c")))
(setq currobj (ssadd (entlast) currobj))
(command "_layer" "set" "nitride" "")
(command "_layer" "set" "fda1" "")
(setq coords (list 
(list 3840.5625 -29.1263) 
(list 3914.585 -29.8763) 
(list 3914.585 -29.6993) 
(list 3840.5625 -29.0493)))
(apply 'command (append '("pline") coords '("c")))
(setq currobj (ssadd (entlast) currobj))
(setq coords (list 
(list 3840.5625 -28.9063) 
(list 3914.585 -29.5563) 
(list 3914.585 -29.3793) 
(list 3840.5625 -28.8293)))
(apply 'command (append '("pline") coords '("c")))
(setq currobj (ssadd (entlast) currobj))
(setq coords (list 
(list 3840.5625 -28.6863) 
(list 3914.585 -29.2363) 
(list 3914.585 -29.0593) 
(list 3840.5625 -28.6093)))
(apply 'command (append '("pline") coords '("c")))
(setq currobj (ssadd (entlast) currobj))
(setq coords (list 
(list 3840.5625 -28.4663) 
(list 3914.585 -28.9163) 
(list 3914.585 -28.7393) 
(list 3840.5625 -28.3893)))
(apply 'command (append '("pline") coords '("c")))
(setq currobj (ssadd (entlast) currobj))
(setq coords (list 
(list 3840.5625 -28.2463) 
(list 3914.585 -28.5963) 
(list 3914.585 -28.4193) 
(list 3840.5625 -28.1693)))
(apply 'command (append '("pline") coords '("c")))
(setq currobj (ssadd (entlast) currobj))
(setq coords (list 
(list 3840.5625 -28.0263) 
(list 3914.585 -28.2763) 
(list 3914.585 -28.0993) 
(list 3840.5625 -27.9493)))
(apply 'command (append '("pline") coords '("c")))
(setq currobj (ssadd (entlast) currobj))
(setq coords (list 
(list 3840.5625 -27.8063) 
(list 3914.585 -27.9563) 
(list 3914.585 -27.7793) 
(list 3840.5625 -27.7293)))
(apply 'command (append '("pline") coords '("c")))
(setq currobj (ssadd (entlast) currobj))
(setq coords (list 
(list 3840.5625 -27.5863) 
(list 3914.585 -27.6363) 
(list 3914.585 -27.4593) 
(list 3840.5625 -27.5093)))
(apply 'command (append '("pline") coords '("c")))
(setq currobj (ssadd (entlast) currobj))
(setq coords (list 
(list 3840.5625 -27.3663) 
(list 3914.585 -27.3163) 
(list 3914.585 -27.1393) 
(list 3840.5625 -27.2893)))
(apply 'command (append '("pline") coords '("c")))
(setq currobj (ssadd (entlast) currobj))
(setq coords (list 
(list 3840.5625 -27.1463) 
(list 3914.585 -26.9963) 
(list 3914.585 -26.8193) 
(list 3840.5625 -27.0693)))
(apply 'command (append '("pline") coords '("c")))
(setq currobj (ssadd (entlast) currobj))
(setq coords (list 
(list 3840.5625 -26.9263) 
(list 3914.585 -26.6763) 
(list 3914.585 -26.4993) 
(list 3840.5625 -26.8493)))
(apply 'command (append '("pline") coords '("c")))
(setq currobj (ssadd (entlast) currobj))
(setq coords (list 
(list 3840.5625 -26.7063) 
(list 3914.585 -26.3563) 
(list 3914.585 -26.1793) 
(list 3840.5625 -26.6293)))
(apply 'command (append '("pline") coords '("c")))
(setq currobj (ssadd (entlast) currobj))
(setq coords (list 
(list 3840.5625 -26.4863) 
(list 3914.585 -26.0363) 
(list 3914.585 -25.8593) 
(list 3840.5625 -26.4093)))
(apply 'command (append '("pline") coords '("c")))
(setq currobj (ssadd (entlast) currobj))
(setq coords (list 
(list 3840.5625 -26.2663) 
(list 3914.585 -25.7163) 
(list 3914.585 -25.5393) 
(list 3840.5625 -26.1893)))
(apply 'command (append '("pline") coords '("c")))
(setq currobj (ssadd (entlast) currobj))
(setq coords (list 
(list 3840.5625 -26.0463) 
(list 3914.585 -25.3963) 
(list 3914.585 -25.2193) 
(list 3840.5625 -25.9693)))
(apply 'command (append '("pline") coords '("c")))
(setq currobj (ssadd (entlast) currobj))
(setq coords (list 
(list 3839.4375 -25.9693) 
(list 3765.415 -25.2193) 
(list 3765.415 -25.3963) 
(list 3839.4375 -26.0463)))
(apply 'command (append '("pline") coords '("c")))
(setq currobj (ssadd (entlast) currobj))
(setq coords (list 
(list 3839.4375 -26.1893) 
(list 3765.415 -25.5393) 
(list 3765.415 -25.7163) 
(list 3839.4375 -26.2663)))
(apply 'command (append '("pline") coords '("c")))
(setq currobj (ssadd (entlast) currobj))
(setq coords (list 
(list 3839.4375 -26.4093) 
(list 3765.415 -25.8593) 
(list 3765.415 -26.0363) 
(list 3839.4375 -26.4863)))
(apply 'command (append '("pline") coords '("c")))
(setq currobj (ssadd (entlast) currobj))
(setq coords (list 
(list 3839.4375 -26.6293) 
(list 3765.415 -26.1793) 
(list 3765.415 -26.3563) 
(list 3839.4375 -26.7063)))
(apply 'command (append '("pline") coords '("c")))
(setq currobj (ssadd (entlast) currobj))
(setq coords (list 
(list 3839.4375 -26.8493) 
(list 3765.415 -26.4993) 
(list 3765.415 -26.6763) 
(list 3839.4375 -26.9263)))
(apply 'command (append '("pline") coords '("c")))
(setq currobj (ssadd (entlast) currobj))
(setq coords (list 
(list 3839.4375 -27.0693) 
(list 3765.415 -26.8193) 
(list 3765.415 -26.9963) 
(list 3839.4375 -27.1463)))
(apply 'command (append '("pline") coords '("c")))
(setq currobj (ssadd (entlast) currobj))
(setq coords (list 
(list 3839.4375 -27.2893) 
(list 3765.415 -27.1393) 
(list 3765.415 -27.3163) 
(list 3839.4375 -27.3663)))
(apply 'command (append '("pline") coords '("c")))
(setq currobj (ssadd (entlast) currobj))
(setq coords (list 
(list 3839.4375 -27.5093) 
(list 3765.415 -27.4593) 
(list 3765.415 -27.6363) 
(list 3839.4375 -27.5863)))
(apply 'command (append '("pline") coords '("c")))
(setq currobj (ssadd (entlast) currobj))
(setq coords (list 
(list 3839.4375 -27.7293) 
(list 3765.415 -27.7793) 
(list 3765.415 -27.9563) 
(list 3839.4375 -27.8063)))
(apply 'command (append '("pline") coords '("c")))
(setq currobj (ssadd (entlast) currobj))
(setq coords (list 
(list 3839.4375 -27.9493) 
(list 3765.415 -28.0993) 
(list 3765.415 -28.2763) 
(list 3839.4375 -28.0263)))
(apply 'command (append '("pline") coords '("c")))
(setq currobj (ssadd (entlast) currobj))
(setq coords (list 
(list 3839.4375 -28.1693) 
(list 3765.415 -28.4193) 
(list 3765.415 -28.5963) 
(list 3839.4375 -28.2463)))
(apply 'command (append '("pline") coords '("c")))
(setq currobj (ssadd (entlast) currobj))
(setq coords (list 
(list 3839.4375 -28.3893) 
(list 3765.415 -28.7393) 
(list 3765.415 -28.9163) 
(list 3839.4375 -28.4663)))
(apply 'command (append '("pline") coords '("c")))
(setq currobj (ssadd (entlast) currobj))
(setq coords (list 
(list 3839.4375 -28.6093) 
(list 3765.415 -29.0593) 
(list 3765.415 -29.2363) 
(list 3839.4375 -28.6863)))
(apply 'command (append '("pline") coords '("c")))
(setq currobj (ssadd (entlast) currobj))
(setq coords (list 
(list 3839.4375 -28.8293) 
(list 3765.415 -29.3793) 
(list 3765.415 -29.5563) 
(list 3839.4375 -28.9063)))
(apply 'command (append '("pline") coords '("c")))
(setq currobj (ssadd (entlast) currobj))
(setq coords (list 
(list 3839.4375 -29.0493) 
(list 3765.415 -29.6993) 
(list 3765.415 -29.8763) 
(list 3839.4375 -29.1263)))
(apply 'command (append '("pline") coords '("c")))
(setq currobj (ssadd (entlast) currobj))
(command "_layer" "set" "nitride" "")
(command "_layer" "set" "text" "")
(command "_circle" "3839.0625,-40.2693" "0.075")
(command "_circle" "3839.0625,-39.9693" "0.075")
(command "_circle" "3839.0625,-39.6693" "0.075")
(command "_circle" "3839.0625,-39.3693" "0.075")
(command "_circle" "3839.0625,-39.0693" "0.075")
(command "_circle" "3838.7625,-40.2693" "0.075")
(command "_circle" "3838.7625,-39.9693" "0.075")
(command "_circle" "3838.7625,-39.6693" "0.075")
(command "_circle" "3838.7625,-39.3693" "0.075")
(command "_circle" "3838.7625,-39.0693" "0.075")
(command "_circle" "3838.4625,-40.2693" "0.075")
(command "_circle" "3838.4625,-39.9693" "0.075")
(command "_circle" "3838.4625,-39.6693" "0.075")
(command "_circle" "3838.4625,-39.3693" "0.075")
(command "_circle" "3838.4625,-39.0693" "0.075")
(command "_circle" "3838.1625,-40.2693" "0.075")
(command "_circle" "3838.1625,-39.9693" "0.075")
(command "_circle" "3838.1625,-39.6693" "0.075")
(command "_circle" "3838.1625,-39.3693" "0.075")
(command "_circle" "3838.1625,-39.0693" "0.075")
(command "_circle" "3837.8625,-40.2693" "0.075")
(command "_circle" "3837.8625,-39.9693" "0.075")
(command "_circle" "3837.8625,-39.6693" "0.075")
(command "_circle" "3837.8625,-39.3693" "0.075")
(command "_circle" "3837.8625,-39.0693" "0.075")
(command "_layer" "set" "nitride" "")
(setq coords (list 
(list 3840.2625 -14.8263) 
(list 3840.2625 100.8184) 
(list 3839.7375 100.8184) 
(list 3839.7375 -14.8263)))
(apply 'command (append '("pline") coords '("c")))
(setq currobj (ssadd (entlast) currobj))
(command "_layer" "set" "prebias" "")
(command "_rectangle" "3839.7375,-14.8263" "3840.2625,100.8184")
(setq currobj (ssadd (entlast) currobj))
(command "_layer" "set" "nitride" "")
(setq coords (list 
(list 3840.2625 100.8184) 
(list 3840.5625 110.8184) 
(list 3840.5625 110.8184) 
(list 3840.5625 111.8184) 
(list 3914.585 111.0684) 
(list 3914.585 116.0114) 
(list 3840.5625 115.2614) 
(list 3840.5625 116.2614) 
(list 3840.5625 116.2614) 
(list 3840.2625 126.2614) 
(list 3839.7375 126.2614) 
(list 3839.4375 116.2614) 
(list 3839.4375 116.2614) 
(list 3839.4375 115.2614) 
(list 3765.415 116.0114) 
(list 3765.415 111.0684) 
(list 3839.4375 111.8184) 
(list 3839.4375 110.8184) 
(list 3839.4375 110.8184) 
(list 3839.7375 100.8184)))
(apply 'command (append '("pline") coords '("c")))
(setq currobj (ssadd (entlast) currobj))
(command "_layer" "set" "prebias" "")
(setq coords (list 
(list 3839.4375 100.8184) 
(list 3839.4375 111.8184) 
(list 3765.415 111.0684) 
(list 3765.415 116.0114) 
(list 3839.4375 115.2614) 
(list 3839.4375 126.2614) 
(list 3840.5625 126.2614) 
(list 3840.5625 115.2614) 
(list 3914.585 116.0114) 
(list 3914.585 111.0684) 
(list 3840.5625 111.8184) 
(list 3840.5625 100.8184)))
(apply 'command (append '("pline") coords '("c")))
(setq currobj (ssadd (entlast) currobj))
(command "_layer" "set" "nitride" "")
(command "_layer" "set" "fda1" "")
(setq coords (list 
(list 3840.5625 111.9614) 
(list 3914.585 111.2114) 
(list 3914.585 111.3884) 
(list 3840.5625 112.0384)))
(apply 'command (append '("pline") coords '("c")))
(setq currobj (ssadd (entlast) currobj))
(setq coords (list 
(list 3840.5625 112.1814) 
(list 3914.585 111.5314) 
(list 3914.585 111.7084) 
(list 3840.5625 112.2584)))
(apply 'command (append '("pline") coords '("c")))
(setq currobj (ssadd (entlast) currobj))
(setq coords (list 
(list 3840.5625 112.4014) 
(list 3914.585 111.8514) 
(list 3914.585 112.0284) 
(list 3840.5625 112.4784)))
(apply 'command (append '("pline") coords '("c")))
(setq currobj (ssadd (entlast) currobj))
(setq coords (list 
(list 3840.5625 112.6214) 
(list 3914.585 112.1714) 
(list 3914.585 112.3484) 
(list 3840.5625 112.6984)))
(apply 'command (append '("pline") coords '("c")))
(setq currobj (ssadd (entlast) currobj))
(setq coords (list 
(list 3840.5625 112.8414) 
(list 3914.585 112.4914) 
(list 3914.585 112.6684) 
(list 3840.5625 112.9184)))
(apply 'command (append '("pline") coords '("c")))
(setq currobj (ssadd (entlast) currobj))
(setq coords (list 
(list 3840.5625 113.0614) 
(list 3914.585 112.8114) 
(list 3914.585 112.9884) 
(list 3840.5625 113.1384)))
(apply 'command (append '("pline") coords '("c")))
(setq currobj (ssadd (entlast) currobj))
(setq coords (list 
(list 3840.5625 113.2814) 
(list 3914.585 113.1314) 
(list 3914.585 113.3084) 
(list 3840.5625 113.3584)))
(apply 'command (append '("pline") coords '("c")))
(setq currobj (ssadd (entlast) currobj))
(setq coords (list 
(list 3840.5625 113.5014) 
(list 3914.585 113.4514) 
(list 3914.585 113.6284) 
(list 3840.5625 113.5784)))
(apply 'command (append '("pline") coords '("c")))
(setq currobj (ssadd (entlast) currobj))
(setq coords (list 
(list 3840.5625 113.7214) 
(list 3914.585 113.7714) 
(list 3914.585 113.9484) 
(list 3840.5625 113.7984)))
(apply 'command (append '("pline") coords '("c")))
(setq currobj (ssadd (entlast) currobj))
(setq coords (list 
(list 3840.5625 113.9414) 
(list 3914.585 114.0914) 
(list 3914.585 114.2684) 
(list 3840.5625 114.0184)))
(apply 'command (append '("pline") coords '("c")))
(setq currobj (ssadd (entlast) currobj))
(setq coords (list 
(list 3840.5625 114.1614) 
(list 3914.585 114.4114) 
(list 3914.585 114.5884) 
(list 3840.5625 114.2384)))
(apply 'command (append '("pline") coords '("c")))
(setq currobj (ssadd (entlast) currobj))
(setq coords (list 
(list 3840.5625 114.3814) 
(list 3914.585 114.7314) 
(list 3914.585 114.9084) 
(list 3840.5625 114.4584)))
(apply 'command (append '("pline") coords '("c")))
(setq currobj (ssadd (entlast) currobj))
(setq coords (list 
(list 3840.5625 114.6014) 
(list 3914.585 115.0514) 
(list 3914.585 115.2284) 
(list 3840.5625 114.6784)))
(apply 'command (append '("pline") coords '("c")))
(setq currobj (ssadd (entlast) currobj))
(setq coords (list 
(list 3840.5625 114.8214) 
(list 3914.585 115.3714) 
(list 3914.585 115.5484) 
(list 3840.5625 114.8984)))
(apply 'command (append '("pline") coords '("c")))
(setq currobj (ssadd (entlast) currobj))
(setq coords (list 
(list 3840.5625 115.0414) 
(list 3914.585 115.6914) 
(list 3914.585 115.8684) 
(list 3840.5625 115.1184)))
(apply 'command (append '("pline") coords '("c")))
(setq currobj (ssadd (entlast) currobj))
(setq coords (list 
(list 3839.4375 115.1184) 
(list 3765.415 115.8684) 
(list 3765.415 115.6914) 
(list 3839.4375 115.0414)))
(apply 'command (append '("pline") coords '("c")))
(setq currobj (ssadd (entlast) currobj))
(setq coords (list 
(list 3839.4375 114.8984) 
(list 3765.415 115.5484) 
(list 3765.415 115.3714) 
(list 3839.4375 114.8214)))
(apply 'command (append '("pline") coords '("c")))
(setq currobj (ssadd (entlast) currobj))
(setq coords (list 
(list 3839.4375 114.6784) 
(list 3765.415 115.2284) 
(list 3765.415 115.0514) 
(list 3839.4375 114.6014)))
(apply 'command (append '("pline") coords '("c")))
(setq currobj (ssadd (entlast) currobj))
(setq coords (list 
(list 3839.4375 114.4584) 
(list 3765.415 114.9084) 
(list 3765.415 114.7314) 
(list 3839.4375 114.3814)))
(apply 'command (append '("pline") coords '("c")))
(setq currobj (ssadd (entlast) currobj))
(setq coords (list 
(list 3839.4375 114.2384) 
(list 3765.415 114.5884) 
(list 3765.415 114.4114) 
(list 3839.4375 114.1614)))
(apply 'command (append '("pline") coords '("c")))
(setq currobj (ssadd (entlast) currobj))
(setq coords (list 
(list 3839.4375 114.0184) 
(list 3765.415 114.2684) 
(list 3765.415 114.0914) 
(list 3839.4375 113.9414)))
(apply 'command (append '("pline") coords '("c")))
(setq currobj (ssadd (entlast) currobj))
(setq coords (list 
(list 3839.4375 113.7984) 
(list 3765.415 113.9484) 
(list 3765.415 113.7714) 
(list 3839.4375 113.7214)))
(apply 'command (append '("pline") coords '("c")))
(setq currobj (ssadd (entlast) currobj))
(setq coords (list 
(list 3839.4375 113.5784) 
(list 3765.415 113.6284) 
(list 3765.415 113.4514) 
(list 3839.4375 113.5014)))
(apply 'command (append '("pline") coords '("c")))
(setq currobj (ssadd (entlast) currobj))
(setq coords (list 
(list 3839.4375 113.3584) 
(list 3765.415 113.3084) 
(list 3765.415 113.1314) 
(list 3839.4375 113.2814)))
(apply 'command (append '("pline") coords '("c")))
(setq currobj (ssadd (entlast) currobj))
(setq coords (list 
(list 3839.4375 113.1384) 
(list 3765.415 112.9884) 
(list 3765.415 112.8114) 
(list 3839.4375 113.0614)))
(apply 'command (append '("pline") coords '("c")))
(setq currobj (ssadd (entlast) currobj))
(setq coords (list 
(list 3839.4375 112.9184) 
(list 3765.415 112.6684) 
(list 3765.415 112.4914) 
(list 3839.4375 112.8414)))
(apply 'command (append '("pline") coords '("c")))
(setq currobj (ssadd (entlast) currobj))
(setq coords (list 
(list 3839.4375 112.6984) 
(list 3765.415 112.3484) 
(list 3765.415 112.1714) 
(list 3839.4375 112.6214)))
(apply 'command (append '("pline") coords '("c")))
(setq currobj (ssadd (entlast) currobj))
(setq coords (list 
(list 3839.4375 112.4784) 
(list 3765.415 112.0284) 
(list 3765.415 111.8514) 
(list 3839.4375 112.4014)))
(apply 'command (append '("pline") coords '("c")))
(setq currobj (ssadd (entlast) currobj))
(setq coords (list 
(list 3839.4375 112.2584) 
(list 3765.415 111.7084) 
(list 3765.415 111.5314) 
(list 3839.4375 112.1814)))
(apply 'command (append '("pline") coords '("c")))
(setq currobj (ssadd (entlast) currobj))
(setq coords (list 
(list 3839.4375 112.0384) 
(list 3765.415 111.3884) 
(list 3765.415 111.2114) 
(list 3839.4375 111.9614)))
(apply 'command (append '("pline") coords '("c")))
(setq currobj (ssadd (entlast) currobj))
(command "_layer" "set" "nitride" "")
(command "_layer" "set" "text" "")
(command "_circle" "3839.0625,100.8184" "0.075")
(command "_circle" "3839.0625,101.1184" "0.075")
(command "_circle" "3839.0625,101.4184" "0.075")
(command "_circle" "3839.0625,101.7184" "0.075")
(command "_circle" "3839.0625,102.0184" "0.075")
(command "_circle" "3838.7625,100.8184" "0.075")
(command "_circle" "3838.7625,101.1184" "0.075")
(command "_circle" "3838.7625,101.4184" "0.075")
(command "_circle" "3838.7625,101.7184" "0.075")
(command "_circle" "3838.7625,102.0184" "0.075")
(command "_circle" "3838.4625,100.8184" "0.075")
(command "_circle" "3838.4625,101.1184" "0.075")
(command "_circle" "3838.4625,101.4184" "0.075")
(command "_circle" "3838.4625,101.7184" "0.075")
(command "_circle" "3838.4625,102.0184" "0.075")
(command "_circle" "3838.1625,100.8184" "0.075")
(command "_circle" "3838.1625,101.1184" "0.075")
(command "_circle" "3838.1625,101.4184" "0.075")
(command "_circle" "3838.1625,101.7184" "0.075")
(command "_circle" "3838.1625,102.0184" "0.075")
(command "_circle" "3837.8625,100.8184" "0.075")
(command "_circle" "3837.8625,101.1184" "0.075")
(command "_circle" "3837.8625,101.4184" "0.075")
(command "_circle" "3837.8625,101.7184" "0.075")
(command "_circle" "3837.8625,102.0184" "0.075")
(command "_layer" "set" "nitride" "")
(setq coords (list 
(list 3840.2625 126.2614) 
(list 3840.2625 241.9061) 
(list 3839.7375 241.9061) 
(list 3839.7375 126.2614)))
(apply 'command (append '("pline") coords '("c")))
(setq currobj (ssadd (entlast) currobj))
(command "_layer" "set" "prebias" "")
(command "_rectangle" "3839.7375,126.2614" "3840.2625,241.9061")
(setq currobj (ssadd (entlast) currobj))
(command "_layer" "set" "nitride" "")
(setq coords (list 
(list 3840.2625 241.9061) 
(list 3840.5625 251.9061) 
(list 3840.5625 251.9061) 
(list 3840.5625 252.9061) 
(list 3914.585 252.1561) 
(list 3914.585 257.0991) 
(list 3840.5625 256.3491) 
(list 3840.5625 257.3491) 
(list 3840.5625 257.3491) 
(list 3840.2625 267.3491) 
(list 3839.7375 267.3491) 
(list 3839.4375 257.3491) 
(list 3839.4375 257.3491) 
(list 3839.4375 256.3491) 
(list 3765.415 257.0991) 
(list 3765.415 252.1561) 
(list 3839.4375 252.9061) 
(list 3839.4375 251.9061) 
(list 3839.4375 251.9061) 
(list 3839.7375 241.9061)))
(apply 'command (append '("pline") coords '("c")))
(setq currobj (ssadd (entlast) currobj))
(command "_layer" "set" "prebias" "")
(setq coords (list 
(list 3839.4375 241.9061) 
(list 3839.4375 252.9061) 
(list 3765.415 252.1561) 
(list 3765.415 257.0991) 
(list 3839.4375 256.3491) 
(list 3839.4375 267.3491) 
(list 3840.5625 267.3491) 
(list 3840.5625 256.3491) 
(list 3914.585 257.0991) 
(list 3914.585 252.1561) 
(list 3840.5625 252.9061) 
(list 3840.5625 241.9061)))
(apply 'command (append '("pline") coords '("c")))
(setq currobj (ssadd (entlast) currobj))
(command "_layer" "set" "nitride" "")
(command "_layer" "set" "fda1" "")
(setq coords (list 
(list 3840.5625 253.0491) 
(list 3914.585 252.2991) 
(list 3914.585 252.4761) 
(list 3840.5625 253.1261)))
(apply 'command (append '("pline") coords '("c")))
(setq currobj (ssadd (entlast) currobj))
(setq coords (list 
(list 3840.5625 253.2691) 
(list 3914.585 252.6191) 
(list 3914.585 252.7961) 
(list 3840.5625 253.3461)))
(apply 'command (append '("pline") coords '("c")))
(setq currobj (ssadd (entlast) currobj))
(setq coords (list 
(list 3840.5625 253.4891) 
(list 3914.585 252.9391) 
(list 3914.585 253.1161) 
(list 3840.5625 253.5661)))
(apply 'command (append '("pline") coords '("c")))
(setq currobj (ssadd (entlast) currobj))
(setq coords (list 
(list 3840.5625 253.7091) 
(list 3914.585 253.2591) 
(list 3914.585 253.4361) 
(list 3840.5625 253.7861)))
(apply 'command (append '("pline") coords '("c")))
(setq currobj (ssadd (entlast) currobj))
(setq coords (list 
(list 3840.5625 253.9291) 
(list 3914.585 253.5791) 
(list 3914.585 253.7561) 
(list 3840.5625 254.0061)))
(apply 'command (append '("pline") coords '("c")))
(setq currobj (ssadd (entlast) currobj))
(setq coords (list 
(list 3840.5625 254.1491) 
(list 3914.585 253.8991) 
(list 3914.585 254.0761) 
(list 3840.5625 254.2261)))
(apply 'command (append '("pline") coords '("c")))
(setq currobj (ssadd (entlast) currobj))
(setq coords (list 
(list 3840.5625 254.3691) 
(list 3914.585 254.2191) 
(list 3914.585 254.3961) 
(list 3840.5625 254.4461)))
(apply 'command (append '("pline") coords '("c")))
(setq currobj (ssadd (entlast) currobj))
(setq coords (list 
(list 3840.5625 254.5891) 
(list 3914.585 254.5391) 
(list 3914.585 254.7161) 
(list 3840.5625 254.6661)))
(apply 'command (append '("pline") coords '("c")))
(setq currobj (ssadd (entlast) currobj))
(setq coords (list 
(list 3840.5625 254.8091) 
(list 3914.585 254.8591) 
(list 3914.585 255.0361) 
(list 3840.5625 254.8861)))
(apply 'command (append '("pline") coords '("c")))
(setq currobj (ssadd (entlast) currobj))
(setq coords (list 
(list 3840.5625 255.0291) 
(list 3914.585 255.1791) 
(list 3914.585 255.3561) 
(list 3840.5625 255.1061)))
(apply 'command (append '("pline") coords '("c")))
(setq currobj (ssadd (entlast) currobj))
(setq coords (list 
(list 3840.5625 255.2491) 
(list 3914.585 255.4991) 
(list 3914.585 255.6761) 
(list 3840.5625 255.3261)))
(apply 'command (append '("pline") coords '("c")))
(setq currobj (ssadd (entlast) currobj))
(setq coords (list 
(list 3840.5625 255.4691) 
(list 3914.585 255.8191) 
(list 3914.585 255.9961) 
(list 3840.5625 255.5461)))
(apply 'command (append '("pline") coords '("c")))
(setq currobj (ssadd (entlast) currobj))
(setq coords (list 
(list 3840.5625 255.6891) 
(list 3914.585 256.1391) 
(list 3914.585 256.3161) 
(list 3840.5625 255.7661)))
(apply 'command (append '("pline") coords '("c")))
(setq currobj (ssadd (entlast) currobj))
(setq coords (list 
(list 3840.5625 255.9091) 
(list 3914.585 256.4591) 
(list 3914.585 256.6361) 
(list 3840.5625 255.9861)))
(apply 'command (append '("pline") coords '("c")))
(setq currobj (ssadd (entlast) currobj))
(setq coords (list 
(list 3840.5625 256.1291) 
(list 3914.585 256.7791) 
(list 3914.585 256.9561) 
(list 3840.5625 256.2061)))
(apply 'command (append '("pline") coords '("c")))
(setq currobj (ssadd (entlast) currobj))
(setq coords (list 
(list 3839.4375 256.2061) 
(list 3765.415 256.9561) 
(list 3765.415 256.7791) 
(list 3839.4375 256.1291)))
(apply 'command (append '("pline") coords '("c")))
(setq currobj (ssadd (entlast) currobj))
(setq coords (list 
(list 3839.4375 255.9861) 
(list 3765.415 256.6361) 
(list 3765.415 256.4591) 
(list 3839.4375 255.9091)))
(apply 'command (append '("pline") coords '("c")))
(setq currobj (ssadd (entlast) currobj))
(setq coords (list 
(list 3839.4375 255.7661) 
(list 3765.415 256.3161) 
(list 3765.415 256.1391) 
(list 3839.4375 255.6891)))
(apply 'command (append '("pline") coords '("c")))
(setq currobj (ssadd (entlast) currobj))
(setq coords (list 
(list 3839.4375 255.5461) 
(list 3765.415 255.9961) 
(list 3765.415 255.8191) 
(list 3839.4375 255.4691)))
(apply 'command (append '("pline") coords '("c")))
(setq currobj (ssadd (entlast) currobj))
(setq coords (list 
(list 3839.4375 255.3261) 
(list 3765.415 255.6761) 
(list 3765.415 255.4991) 
(list 3839.4375 255.2491)))
(apply 'command (append '("pline") coords '("c")))
(setq currobj (ssadd (entlast) currobj))
(setq coords (list 
(list 3839.4375 255.1061) 
(list 3765.415 255.3561) 
(list 3765.415 255.1791) 
(list 3839.4375 255.0291)))
(apply 'command (append '("pline") coords '("c")))
(setq currobj (ssadd (entlast) currobj))
(setq coords (list 
(list 3839.4375 254.8861) 
(list 3765.415 255.0361) 
(list 3765.415 254.8591) 
(list 3839.4375 254.8091)))
(apply 'command (append '("pline") coords '("c")))
(setq currobj (ssadd (entlast) currobj))
(setq coords (list 
(list 3839.4375 254.6661) 
(list 3765.415 254.7161) 
(list 3765.415 254.5391) 
(list 3839.4375 254.5891)))
(apply 'command (append '("pline") coords '("c")))
(setq currobj (ssadd (entlast) currobj))
(setq coords (list 
(list 3839.4375 254.4461) 
(list 3765.415 254.3961) 
(list 3765.415 254.2191) 
(list 3839.4375 254.3691)))
(apply 'command (append '("pline") coords '("c")))
(setq currobj (ssadd (entlast) currobj))
(setq coords (list 
(list 3839.4375 254.2261) 
(list 3765.415 254.0761) 
(list 3765.415 253.8991) 
(list 3839.4375 254.1491)))
(apply 'command (append '("pline") coords '("c")))
(setq currobj (ssadd (entlast) currobj))
(setq coords (list 
(list 3839.4375 254.0061) 
(list 3765.415 253.7561) 
(list 3765.415 253.5791) 
(list 3839.4375 253.9291)))
(apply 'command (append '("pline") coords '("c")))
(setq currobj (ssadd (entlast) currobj))
(setq coords (list 
(list 3839.4375 253.7861) 
(list 3765.415 253.4361) 
(list 3765.415 253.2591) 
(list 3839.4375 253.7091)))
(apply 'command (append '("pline") coords '("c")))
(setq currobj (ssadd (entlast) currobj))
(setq coords (list 
(list 3839.4375 253.5661) 
(list 3765.415 253.1161) 
(list 3765.415 252.9391) 
(list 3839.4375 253.4891)))
(apply 'command (append '("pline") coords '("c")))
(setq currobj (ssadd (entlast) currobj))
(setq coords (list 
(list 3839.4375 253.3461) 
(list 3765.415 252.7961) 
(list 3765.415 252.6191) 
(list 3839.4375 253.2691)))
(apply 'command (append '("pline") coords '("c")))
(setq currobj (ssadd (entlast) currobj))
(setq coords (list 
(list 3839.4375 253.1261) 
(list 3765.415 252.4761) 
(list 3765.415 252.2991) 
(list 3839.4375 253.0491)))
(apply 'command (append '("pline") coords '("c")))
(setq currobj (ssadd (entlast) currobj))
(command "_layer" "set" "nitride" "")
(command "_layer" "set" "text" "")
(command "_circle" "3839.0625,241.9061" "0.075")
(command "_circle" "3839.0625,242.2061" "0.075")
(command "_circle" "3839.0625,242.5061" "0.075")
(command "_circle" "3839.0625,242.8061" "0.075")
(command "_circle" "3839.0625,243.1061" "0.075")
(command "_circle" "3838.7625,241.9061" "0.075")
(command "_circle" "3838.7625,242.2061" "0.075")
(command "_circle" "3838.7625,242.5061" "0.075")
(command "_circle" "3838.7625,242.8061" "0.075")
(command "_circle" "3838.7625,243.1061" "0.075")
(command "_circle" "3838.4625,241.9061" "0.075")
(command "_circle" "3838.4625,242.2061" "0.075")
(command "_circle" "3838.4625,242.5061" "0.075")
(command "_circle" "3838.4625,242.8061" "0.075")
(command "_circle" "3838.4625,243.1061" "0.075")
(command "_circle" "3838.1625,241.9061" "0.075")
(command "_circle" "3838.1625,242.2061" "0.075")
(command "_circle" "3838.1625,242.5061" "0.075")
(command "_circle" "3838.1625,242.8061" "0.075")
(command "_circle" "3838.1625,243.1061" "0.075")
(command "_circle" "3837.8625,241.9061" "0.075")
(command "_circle" "3837.8625,242.2061" "0.075")
(command "_circle" "3837.8625,242.5061" "0.075")
(command "_circle" "3837.8625,242.8061" "0.075")
(command "_circle" "3837.8625,243.1061" "0.075")
(command "_layer" "set" "nitride" "")
(setq coords (list 
(list 3840.2625 267.3491) 
(list 3840.2625 382.9939) 
(list 3839.7375 382.9939) 
(list 3839.7375 267.3491)))
(apply 'command (append '("pline") coords '("c")))
(setq currobj (ssadd (entlast) currobj))
(command "_layer" "set" "prebias" "")
(command "_rectangle" "3839.7375,267.3491" "3840.2625,382.9939")
(setq currobj (ssadd (entlast) currobj))
(command "_layer" "set" "nitride" "")
(setq coords (list 
(list 3840.2625 382.9939) 
(list 3840.5625 392.9939) 
(list 3840.5625 392.9939) 
(list 3840.5625 393.9939) 
(list 3914.585 393.2439) 
(list 3914.585 398.1869) 
(list 3840.5625 397.4369) 
(list 3840.5625 398.4369) 
(list 3840.5625 398.4369) 
(list 3840.2625 408.4369) 
(list 3839.7375 408.4369) 
(list 3839.4375 398.4369) 
(list 3839.4375 398.4369) 
(list 3839.4375 397.4369) 
(list 3765.415 398.1869) 
(list 3765.415 393.2439) 
(list 3839.4375 393.9939) 
(list 3839.4375 392.9939) 
(list 3839.4375 392.9939) 
(list 3839.7375 382.9939)))
(apply 'command (append '("pline") coords '("c")))
(setq currobj (ssadd (entlast) currobj))
(command "_layer" "set" "prebias" "")
(setq coords (list 
(list 3839.4375 382.9939) 
(list 3839.4375 393.9939) 
(list 3765.415 393.2439) 
(list 3765.415 398.1869) 
(list 3839.4375 397.4369) 
(list 3839.4375 408.4369) 
(list 3840.5625 408.4369) 
(list 3840.5625 397.4369) 
(list 3914.585 398.1869) 
(list 3914.585 393.2439) 
(list 3840.5625 393.9939) 
(list 3840.5625 382.9939)))
(apply 'command (append '("pline") coords '("c")))
(setq currobj (ssadd (entlast) currobj))
(command "_layer" "set" "nitride" "")
(command "_layer" "set" "fda1" "")
(setq coords (list 
(list 3840.5625 394.1369) 
(list 3914.585 393.3869) 
(list 3914.585 393.5639) 
(list 3840.5625 394.2139)))
(apply 'command (append '("pline") coords '("c")))
(setq currobj (ssadd (entlast) currobj))
(setq coords (list 
(list 3840.5625 394.3569) 
(list 3914.585 393.7069) 
(list 3914.585 393.8839) 
(list 3840.5625 394.4339)))
(apply 'command (append '("pline") coords '("c")))
(setq currobj (ssadd (entlast) currobj))
(setq coords (list 
(list 3840.5625 394.5769) 
(list 3914.585 394.0269) 
(list 3914.585 394.2039) 
(list 3840.5625 394.6539)))
(apply 'command (append '("pline") coords '("c")))
(setq currobj (ssadd (entlast) currobj))
(setq coords (list 
(list 3840.5625 394.7969) 
(list 3914.585 394.3469) 
(list 3914.585 394.5239) 
(list 3840.5625 394.8739)))
(apply 'command (append '("pline") coords '("c")))
(setq currobj (ssadd (entlast) currobj))
(setq coords (list 
(list 3840.5625 395.0169) 
(list 3914.585 394.6669) 
(list 3914.585 394.8439) 
(list 3840.5625 395.0939)))
(apply 'command (append '("pline") coords '("c")))
(setq currobj (ssadd (entlast) currobj))
(setq coords (list 
(list 3840.5625 395.2369) 
(list 3914.585 394.9869) 
(list 3914.585 395.1639) 
(list 3840.5625 395.3139)))
(apply 'command (append '("pline") coords '("c")))
(setq currobj (ssadd (entlast) currobj))
(setq coords (list 
(list 3840.5625 395.4569) 
(list 3914.585 395.3069) 
(list 3914.585 395.4839) 
(list 3840.5625 395.5339)))
(apply 'command (append '("pline") coords '("c")))
(setq currobj (ssadd (entlast) currobj))
(setq coords (list 
(list 3840.5625 395.6769) 
(list 3914.585 395.6269) 
(list 3914.585 395.8039) 
(list 3840.5625 395.7539)))
(apply 'command (append '("pline") coords '("c")))
(setq currobj (ssadd (entlast) currobj))
(setq coords (list 
(list 3840.5625 395.8969) 
(list 3914.585 395.9469) 
(list 3914.585 396.1239) 
(list 3840.5625 395.9739)))
(apply 'command (append '("pline") coords '("c")))
(setq currobj (ssadd (entlast) currobj))
(setq coords (list 
(list 3840.5625 396.1169) 
(list 3914.585 396.2669) 
(list 3914.585 396.4439) 
(list 3840.5625 396.1939)))
(apply 'command (append '("pline") coords '("c")))
(setq currobj (ssadd (entlast) currobj))
(setq coords (list 
(list 3840.5625 396.3369) 
(list 3914.585 396.5869) 
(list 3914.585 396.7639) 
(list 3840.5625 396.4139)))
(apply 'command (append '("pline") coords '("c")))
(setq currobj (ssadd (entlast) currobj))
(setq coords (list 
(list 3840.5625 396.5569) 
(list 3914.585 396.9069) 
(list 3914.585 397.0839) 
(list 3840.5625 396.6339)))
(apply 'command (append '("pline") coords '("c")))
(setq currobj (ssadd (entlast) currobj))
(setq coords (list 
(list 3840.5625 396.7769) 
(list 3914.585 397.2269) 
(list 3914.585 397.4039) 
(list 3840.5625 396.8539)))
(apply 'command (append '("pline") coords '("c")))
(setq currobj (ssadd (entlast) currobj))
(setq coords (list 
(list 3840.5625 396.9969) 
(list 3914.585 397.5469) 
(list 3914.585 397.7239) 
(list 3840.5625 397.0739)))
(apply 'command (append '("pline") coords '("c")))
(setq currobj (ssadd (entlast) currobj))
(setq coords (list 
(list 3840.5625 397.2169) 
(list 3914.585 397.8669) 
(list 3914.585 398.0439) 
(list 3840.5625 397.2939)))
(apply 'command (append '("pline") coords '("c")))
(setq currobj (ssadd (entlast) currobj))
(setq coords (list 
(list 3839.4375 397.2939) 
(list 3765.415 398.0439) 
(list 3765.415 397.8669) 
(list 3839.4375 397.2169)))
(apply 'command (append '("pline") coords '("c")))
(setq currobj (ssadd (entlast) currobj))
(setq coords (list 
(list 3839.4375 397.0739) 
(list 3765.415 397.7239) 
(list 3765.415 397.5469) 
(list 3839.4375 396.9969)))
(apply 'command (append '("pline") coords '("c")))
(setq currobj (ssadd (entlast) currobj))
(setq coords (list 
(list 3839.4375 396.8539) 
(list 3765.415 397.4039) 
(list 3765.415 397.2269) 
(list 3839.4375 396.7769)))
(apply 'command (append '("pline") coords '("c")))
(setq currobj (ssadd (entlast) currobj))
(setq coords (list 
(list 3839.4375 396.6339) 
(list 3765.415 397.0839) 
(list 3765.415 396.9069) 
(list 3839.4375 396.5569)))
(apply 'command (append '("pline") coords '("c")))
(setq currobj (ssadd (entlast) currobj))
(setq coords (list 
(list 3839.4375 396.4139) 
(list 3765.415 396.7639) 
(list 3765.415 396.5869) 
(list 3839.4375 396.3369)))
(apply 'command (append '("pline") coords '("c")))
(setq currobj (ssadd (entlast) currobj))
(setq coords (list 
(list 3839.4375 396.1939) 
(list 3765.415 396.4439) 
(list 3765.415 396.2669) 
(list 3839.4375 396.1169)))
(apply 'command (append '("pline") coords '("c")))
(setq currobj (ssadd (entlast) currobj))
(setq coords (list 
(list 3839.4375 395.9739) 
(list 3765.415 396.1239) 
(list 3765.415 395.9469) 
(list 3839.4375 395.8969)))
(apply 'command (append '("pline") coords '("c")))
(setq currobj (ssadd (entlast) currobj))
(setq coords (list 
(list 3839.4375 395.7539) 
(list 3765.415 395.8039) 
(list 3765.415 395.6269) 
(list 3839.4375 395.6769)))
(apply 'command (append '("pline") coords '("c")))
(setq currobj (ssadd (entlast) currobj))
(setq coords (list 
(list 3839.4375 395.5339) 
(list 3765.415 395.4839) 
(list 3765.415 395.3069) 
(list 3839.4375 395.4569)))
(apply 'command (append '("pline") coords '("c")))
(setq currobj (ssadd (entlast) currobj))
(setq coords (list 
(list 3839.4375 395.3139) 
(list 3765.415 395.1639) 
(list 3765.415 394.9869) 
(list 3839.4375 395.2369)))
(apply 'command (append '("pline") coords '("c")))
(setq currobj (ssadd (entlast) currobj))
(setq coords (list 
(list 3839.4375 395.0939) 
(list 3765.415 394.8439) 
(list 3765.415 394.6669) 
(list 3839.4375 395.0169)))
(apply 'command (append '("pline") coords '("c")))
(setq currobj (ssadd (entlast) currobj))
(setq coords (list 
(list 3839.4375 394.8739) 
(list 3765.415 394.5239) 
(list 3765.415 394.3469) 
(list 3839.4375 394.7969)))
(apply 'command (append '("pline") coords '("c")))
(setq currobj (ssadd (entlast) currobj))
(setq coords (list 
(list 3839.4375 394.6539) 
(list 3765.415 394.2039) 
(list 3765.415 394.0269) 
(list 3839.4375 394.5769)))
(apply 'command (append '("pline") coords '("c")))
(setq currobj (ssadd (entlast) currobj))
(setq coords (list 
(list 3839.4375 394.4339) 
(list 3765.415 393.8839) 
(list 3765.415 393.7069) 
(list 3839.4375 394.3569)))
(apply 'command (append '("pline") coords '("c")))
(setq currobj (ssadd (entlast) currobj))
(setq coords (list 
(list 3839.4375 394.2139) 
(list 3765.415 393.5639) 
(list 3765.415 393.3869) 
(list 3839.4375 394.1369)))
(apply 'command (append '("pline") coords '("c")))
(setq currobj (ssadd (entlast) currobj))
(command "_layer" "set" "nitride" "")
(command "_layer" "set" "text" "")
(command "_circle" "3839.0625,382.9939" "0.075")
(command "_circle" "3839.0625,383.2939" "0.075")
(command "_circle" "3839.0625,383.5939" "0.075")
(command "_circle" "3839.0625,383.8939" "0.075")
(command "_circle" "3839.0625,384.1939" "0.075")
(command "_circle" "3838.7625,382.9939" "0.075")
(command "_circle" "3838.7625,383.2939" "0.075")
(command "_circle" "3838.7625,383.5939" "0.075")
(command "_circle" "3838.7625,383.8939" "0.075")
(command "_circle" "3838.7625,384.1939" "0.075")
(command "_circle" "3838.4625,382.9939" "0.075")
(command "_circle" "3838.4625,383.2939" "0.075")
(command "_circle" "3838.4625,383.5939" "0.075")
(command "_circle" "3838.4625,383.8939" "0.075")
(command "_circle" "3838.4625,384.1939" "0.075")
(command "_circle" "3838.1625,382.9939" "0.075")
(command "_circle" "3838.1625,383.2939" "0.075")
(command "_circle" "3838.1625,383.5939" "0.075")
(command "_circle" "3838.1625,383.8939" "0.075")
(command "_circle" "3838.1625,384.1939" "0.075")
(command "_circle" "3837.8625,382.9939" "0.075")
(command "_circle" "3837.8625,383.2939" "0.075")
(command "_circle" "3837.8625,383.5939" "0.075")
(command "_circle" "3837.8625,383.8939" "0.075")
(command "_circle" "3837.8625,384.1939" "0.075")
(command "_layer" "set" "nitride" "")
(setq coords (list 
(list 3840.2625 408.4369) 
(list 3840.2625 524.0816) 
(list 3839.7375 524.0816) 
(list 3839.7375 408.4369)))
(apply 'command (append '("pline") coords '("c")))
(setq currobj (ssadd (entlast) currobj))
(command "_layer" "set" "prebias" "")
(command "_rectangle" "3839.7375,408.4369" "3840.2625,524.0816")
(setq currobj (ssadd (entlast) currobj))
(command "_layer" "set" "nitride" "")
(setq coords (list 
(list 3840.2625 524.0816) 
(list 3840.5625 534.0816) 
(list 3840.5625 534.0816) 
(list 3840.5625 535.0816) 
(list 3914.585 534.3316) 
(list 3914.585 539.2746) 
(list 3840.5625 538.5246) 
(list 3840.5625 539.5246) 
(list 3840.5625 539.5246) 
(list 3840.2625 549.5246) 
(list 3839.7375 549.5246) 
(list 3839.4375 539.5246) 
(list 3839.4375 539.5246) 
(list 3839.4375 538.5246) 
(list 3765.415 539.2746) 
(list 3765.415 534.3316) 
(list 3839.4375 535.0816) 
(list 3839.4375 534.0816) 
(list 3839.4375 534.0816) 
(list 3839.7375 524.0816)))
(apply 'command (append '("pline") coords '("c")))
(setq currobj (ssadd (entlast) currobj))
(command "_layer" "set" "prebias" "")
(setq coords (list 
(list 3839.4375 524.0816) 
(list 3839.4375 535.0816) 
(list 3765.415 534.3316) 
(list 3765.415 539.2746) 
(list 3839.4375 538.5246) 
(list 3839.4375 549.5246) 
(list 3840.5625 549.5246) 
(list 3840.5625 538.5246) 
(list 3914.585 539.2746) 
(list 3914.585 534.3316) 
(list 3840.5625 535.0816) 
(list 3840.5625 524.0816)))
(apply 'command (append '("pline") coords '("c")))
(setq currobj (ssadd (entlast) currobj))
(command "_layer" "set" "nitride" "")
(command "_layer" "set" "fda1" "")
(setq coords (list 
(list 3840.5625 535.2246) 
(list 3914.585 534.4746) 
(list 3914.585 534.6516) 
(list 3840.5625 535.3016)))
(apply 'command (append '("pline") coords '("c")))
(setq currobj (ssadd (entlast) currobj))
(setq coords (list 
(list 3840.5625 535.4446) 
(list 3914.585 534.7946) 
(list 3914.585 534.9716) 
(list 3840.5625 535.5216)))
(apply 'command (append '("pline") coords '("c")))
(setq currobj (ssadd (entlast) currobj))
(setq coords (list 
(list 3840.5625 535.6646) 
(list 3914.585 535.1146) 
(list 3914.585 535.2916) 
(list 3840.5625 535.7416)))
(apply 'command (append '("pline") coords '("c")))
(setq currobj (ssadd (entlast) currobj))
(setq coords (list 
(list 3840.5625 535.8846) 
(list 3914.585 535.4346) 
(list 3914.585 535.6116) 
(list 3840.5625 535.9616)))
(apply 'command (append '("pline") coords '("c")))
(setq currobj (ssadd (entlast) currobj))
(setq coords (list 
(list 3840.5625 536.1046) 
(list 3914.585 535.7546) 
(list 3914.585 535.9316) 
(list 3840.5625 536.1816)))
(apply 'command (append '("pline") coords '("c")))
(setq currobj (ssadd (entlast) currobj))
(setq coords (list 
(list 3840.5625 536.3246) 
(list 3914.585 536.0746) 
(list 3914.585 536.2516) 
(list 3840.5625 536.4016)))
(apply 'command (append '("pline") coords '("c")))
(setq currobj (ssadd (entlast) currobj))
(setq coords (list 
(list 3840.5625 536.5446) 
(list 3914.585 536.3946) 
(list 3914.585 536.5716) 
(list 3840.5625 536.6216)))
(apply 'command (append '("pline") coords '("c")))
(setq currobj (ssadd (entlast) currobj))
(setq coords (list 
(list 3840.5625 536.7646) 
(list 3914.585 536.7146) 
(list 3914.585 536.8916) 
(list 3840.5625 536.8416)))
(apply 'command (append '("pline") coords '("c")))
(setq currobj (ssadd (entlast) currobj))
(setq coords (list 
(list 3840.5625 536.9846) 
(list 3914.585 537.0346) 
(list 3914.585 537.2116) 
(list 3840.5625 537.0616)))
(apply 'command (append '("pline") coords '("c")))
(setq currobj (ssadd (entlast) currobj))
(setq coords (list 
(list 3840.5625 537.2046) 
(list 3914.585 537.3546) 
(list 3914.585 537.5316) 
(list 3840.5625 537.2816)))
(apply 'command (append '("pline") coords '("c")))
(setq currobj (ssadd (entlast) currobj))
(setq coords (list 
(list 3840.5625 537.4246) 
(list 3914.585 537.6746) 
(list 3914.585 537.8516) 
(list 3840.5625 537.5016)))
(apply 'command (append '("pline") coords '("c")))
(setq currobj (ssadd (entlast) currobj))
(setq coords (list 
(list 3840.5625 537.6446) 
(list 3914.585 537.9946) 
(list 3914.585 538.1716) 
(list 3840.5625 537.7216)))
(apply 'command (append '("pline") coords '("c")))
(setq currobj (ssadd (entlast) currobj))
(setq coords (list 
(list 3840.5625 537.8646) 
(list 3914.585 538.3146) 
(list 3914.585 538.4916) 
(list 3840.5625 537.9416)))
(apply 'command (append '("pline") coords '("c")))
(setq currobj (ssadd (entlast) currobj))
(setq coords (list 
(list 3840.5625 538.0846) 
(list 3914.585 538.6346) 
(list 3914.585 538.8116) 
(list 3840.5625 538.1616)))
(apply 'command (append '("pline") coords '("c")))
(setq currobj (ssadd (entlast) currobj))
(setq coords (list 
(list 3840.5625 538.3046) 
(list 3914.585 538.9546) 
(list 3914.585 539.1316) 
(list 3840.5625 538.3816)))
(apply 'command (append '("pline") coords '("c")))
(setq currobj (ssadd (entlast) currobj))
(setq coords (list 
(list 3839.4375 538.3816) 
(list 3765.415 539.1316) 
(list 3765.415 538.9546) 
(list 3839.4375 538.3046)))
(apply 'command (append '("pline") coords '("c")))
(setq currobj (ssadd (entlast) currobj))
(setq coords (list 
(list 3839.4375 538.1616) 
(list 3765.415 538.8116) 
(list 3765.415 538.6346) 
(list 3839.4375 538.0846)))
(apply 'command (append '("pline") coords '("c")))
(setq currobj (ssadd (entlast) currobj))
(setq coords (list 
(list 3839.4375 537.9416) 
(list 3765.415 538.4916) 
(list 3765.415 538.3146) 
(list 3839.4375 537.8646)))
(apply 'command (append '("pline") coords '("c")))
(setq currobj (ssadd (entlast) currobj))
(setq coords (list 
(list 3839.4375 537.7216) 
(list 3765.415 538.1716) 
(list 3765.415 537.9946) 
(list 3839.4375 537.6446)))
(apply 'command (append '("pline") coords '("c")))
(setq currobj (ssadd (entlast) currobj))
(setq coords (list 
(list 3839.4375 537.5016) 
(list 3765.415 537.8516) 
(list 3765.415 537.6746) 
(list 3839.4375 537.4246)))
(apply 'command (append '("pline") coords '("c")))
(setq currobj (ssadd (entlast) currobj))
(setq coords (list 
(list 3839.4375 537.2816) 
(list 3765.415 537.5316) 
(list 3765.415 537.3546) 
(list 3839.4375 537.2046)))
(apply 'command (append '("pline") coords '("c")))
(setq currobj (ssadd (entlast) currobj))
(setq coords (list 
(list 3839.4375 537.0616) 
(list 3765.415 537.2116) 
(list 3765.415 537.0346) 
(list 3839.4375 536.9846)))
(apply 'command (append '("pline") coords '("c")))
(setq currobj (ssadd (entlast) currobj))
(setq coords (list 
(list 3839.4375 536.8416) 
(list 3765.415 536.8916) 
(list 3765.415 536.7146) 
(list 3839.4375 536.7646)))
(apply 'command (append '("pline") coords '("c")))
(setq currobj (ssadd (entlast) currobj))
(setq coords (list 
(list 3839.4375 536.6216) 
(list 3765.415 536.5716) 
(list 3765.415 536.3946) 
(list 3839.4375 536.5446)))
(apply 'command (append '("pline") coords '("c")))
(setq currobj (ssadd (entlast) currobj))
(setq coords (list 
(list 3839.4375 536.4016) 
(list 3765.415 536.2516) 
(list 3765.415 536.0746) 
(list 3839.4375 536.3246)))
(apply 'command (append '("pline") coords '("c")))
(setq currobj (ssadd (entlast) currobj))
(setq coords (list 
(list 3839.4375 536.1816) 
(list 3765.415 535.9316) 
(list 3765.415 535.7546) 
(list 3839.4375 536.1046)))
(apply 'command (append '("pline") coords '("c")))
(setq currobj (ssadd (entlast) currobj))
(setq coords (list 
(list 3839.4375 535.9616) 
(list 3765.415 535.6116) 
(list 3765.415 535.4346) 
(list 3839.4375 535.8846)))
(apply 'command (append '("pline") coords '("c")))
(setq currobj (ssadd (entlast) currobj))
(setq coords (list 
(list 3839.4375 535.7416) 
(list 3765.415 535.2916) 
(list 3765.415 535.1146) 
(list 3839.4375 535.6646)))
(apply 'command (append '("pline") coords '("c")))
(setq currobj (ssadd (entlast) currobj))
(setq coords (list 
(list 3839.4375 535.5216) 
(list 3765.415 534.9716) 
(list 3765.415 534.7946) 
(list 3839.4375 535.4446)))
(apply 'command (append '("pline") coords '("c")))
(setq currobj (ssadd (entlast) currobj))
(setq coords (list 
(list 3839.4375 535.3016) 
(list 3765.415 534.6516) 
(list 3765.415 534.4746) 
(list 3839.4375 535.2246)))
(apply 'command (append '("pline") coords '("c")))
(setq currobj (ssadd (entlast) currobj))
(command "_layer" "set" "nitride" "")
(command "_layer" "set" "text" "")
(command "_circle" "3839.0625,524.0816" "0.075")
(command "_circle" "3839.0625,524.3816" "0.075")
(command "_circle" "3839.0625,524.6816" "0.075")
(command "_circle" "3839.0625,524.9816" "0.075")
(command "_circle" "3839.0625,525.2816" "0.075")
(command "_circle" "3838.7625,524.0816" "0.075")
(command "_circle" "3838.7625,524.3816" "0.075")
(command "_circle" "3838.7625,524.6816" "0.075")
(command "_circle" "3838.7625,524.9816" "0.075")
(command "_circle" "3838.7625,525.2816" "0.075")
(command "_circle" "3838.4625,524.0816" "0.075")
(command "_circle" "3838.4625,524.3816" "0.075")
(command "_circle" "3838.4625,524.6816" "0.075")
(command "_circle" "3838.4625,524.9816" "0.075")
(command "_circle" "3838.4625,525.2816" "0.075")
(command "_circle" "3838.1625,524.0816" "0.075")
(command "_circle" "3838.1625,524.3816" "0.075")
(command "_circle" "3838.1625,524.6816" "0.075")
(command "_circle" "3838.1625,524.9816" "0.075")
(command "_circle" "3838.1625,525.2816" "0.075")
(command "_circle" "3837.8625,524.0816" "0.075")
(command "_circle" "3837.8625,524.3816" "0.075")
(command "_circle" "3837.8625,524.6816" "0.075")
(command "_circle" "3837.8625,524.9816" "0.075")
(command "_circle" "3837.8625,525.2816" "0.075")
(command "_layer" "set" "nitride" "")
(setq coords (list 
(list 3840.2625 549.5246) 
(list 3840.2625 665.1693) 
(list 3839.7375 665.1693) 
(list 3839.7375 549.5246)))
(apply 'command (append '("pline") coords '("c")))
(setq currobj (ssadd (entlast) currobj))
(command "_layer" "set" "prebias" "")
(command "_rectangle" "3839.7375,549.5246" "3840.2625,665.1693")
(setq currobj (ssadd (entlast) currobj))
(command "_layer" "set" "nitride" "")
(setq coords (list 
(list 3840.2625 665.1693) 
(list 3840.5625 675.1693) 
(list 3840.5625 675.1693) 
(list 3840.5625 676.1693) 
(list 3914.585 675.4193) 
(list 3914.585 680.3623) 
(list 3840.5625 679.6123) 
(list 3840.5625 680.6123) 
(list 3840.5625 680.6123) 
(list 3840.2625 690.6123) 
(list 3839.7375 690.6123) 
(list 3839.4375 680.6123) 
(list 3839.4375 680.6123) 
(list 3839.4375 679.6123) 
(list 3765.415 680.3623) 
(list 3765.415 675.4193) 
(list 3839.4375 676.1693) 
(list 3839.4375 675.1693) 
(list 3839.4375 675.1693) 
(list 3839.7375 665.1693)))
(apply 'command (append '("pline") coords '("c")))
(setq currobj (ssadd (entlast) currobj))
(command "_layer" "set" "prebias" "")
(setq coords (list 
(list 3839.4375 665.1693) 
(list 3839.4375 676.1693) 
(list 3765.415 675.4193) 
(list 3765.415 680.3623) 
(list 3839.4375 679.6123) 
(list 3839.4375 690.6123) 
(list 3840.5625 690.6123) 
(list 3840.5625 679.6123) 
(list 3914.585 680.3623) 
(list 3914.585 675.4193) 
(list 3840.5625 676.1693) 
(list 3840.5625 665.1693)))
(apply 'command (append '("pline") coords '("c")))
(setq currobj (ssadd (entlast) currobj))
(command "_layer" "set" "nitride" "")
(command "_layer" "set" "fda1" "")
(setq coords (list 
(list 3840.5625 676.3123) 
(list 3914.585 675.5623) 
(list 3914.585 675.7393) 
(list 3840.5625 676.3893)))
(apply 'command (append '("pline") coords '("c")))
(setq currobj (ssadd (entlast) currobj))
(setq coords (list 
(list 3840.5625 676.5323) 
(list 3914.585 675.8823) 
(list 3914.585 676.0593) 
(list 3840.5625 676.6093)))
(apply 'command (append '("pline") coords '("c")))
(setq currobj (ssadd (entlast) currobj))
(setq coords (list 
(list 3840.5625 676.7523) 
(list 3914.585 676.2023) 
(list 3914.585 676.3793) 
(list 3840.5625 676.8293)))
(apply 'command (append '("pline") coords '("c")))
(setq currobj (ssadd (entlast) currobj))
(setq coords (list 
(list 3840.5625 676.9723) 
(list 3914.585 676.5223) 
(list 3914.585 676.6993) 
(list 3840.5625 677.0493)))
(apply 'command (append '("pline") coords '("c")))
(setq currobj (ssadd (entlast) currobj))
(setq coords (list 
(list 3840.5625 677.1923) 
(list 3914.585 676.8423) 
(list 3914.585 677.0193) 
(list 3840.5625 677.2693)))
(apply 'command (append '("pline") coords '("c")))
(setq currobj (ssadd (entlast) currobj))
(setq coords (list 
(list 3840.5625 677.4123) 
(list 3914.585 677.1623) 
(list 3914.585 677.3393) 
(list 3840.5625 677.4893)))
(apply 'command (append '("pline") coords '("c")))
(setq currobj (ssadd (entlast) currobj))
(setq coords (list 
(list 3840.5625 677.6323) 
(list 3914.585 677.4823) 
(list 3914.585 677.6593) 
(list 3840.5625 677.7093)))
(apply 'command (append '("pline") coords '("c")))
(setq currobj (ssadd (entlast) currobj))
(setq coords (list 
(list 3840.5625 677.8523) 
(list 3914.585 677.8023) 
(list 3914.585 677.9793) 
(list 3840.5625 677.9293)))
(apply 'command (append '("pline") coords '("c")))
(setq currobj (ssadd (entlast) currobj))
(setq coords (list 
(list 3840.5625 678.0723) 
(list 3914.585 678.1223) 
(list 3914.585 678.2993) 
(list 3840.5625 678.1493)))
(apply 'command (append '("pline") coords '("c")))
(setq currobj (ssadd (entlast) currobj))
(setq coords (list 
(list 3840.5625 678.2923) 
(list 3914.585 678.4423) 
(list 3914.585 678.6193) 
(list 3840.5625 678.3693)))
(apply 'command (append '("pline") coords '("c")))
(setq currobj (ssadd (entlast) currobj))
(setq coords (list 
(list 3840.5625 678.5123) 
(list 3914.585 678.7623) 
(list 3914.585 678.9393) 
(list 3840.5625 678.5893)))
(apply 'command (append '("pline") coords '("c")))
(setq currobj (ssadd (entlast) currobj))
(setq coords (list 
(list 3840.5625 678.7323) 
(list 3914.585 679.0823) 
(list 3914.585 679.2593) 
(list 3840.5625 678.8093)))
(apply 'command (append '("pline") coords '("c")))
(setq currobj (ssadd (entlast) currobj))
(setq coords (list 
(list 3840.5625 678.9523) 
(list 3914.585 679.4023) 
(list 3914.585 679.5793) 
(list 3840.5625 679.0293)))
(apply 'command (append '("pline") coords '("c")))
(setq currobj (ssadd (entlast) currobj))
(setq coords (list 
(list 3840.5625 679.1723) 
(list 3914.585 679.7223) 
(list 3914.585 679.8993) 
(list 3840.5625 679.2493)))
(apply 'command (append '("pline") coords '("c")))
(setq currobj (ssadd (entlast) currobj))
(setq coords (list 
(list 3840.5625 679.3923) 
(list 3914.585 680.0423) 
(list 3914.585 680.2193) 
(list 3840.5625 679.4693)))
(apply 'command (append '("pline") coords '("c")))
(setq currobj (ssadd (entlast) currobj))
(setq coords (list 
(list 3839.4375 679.4693) 
(list 3765.415 680.2193) 
(list 3765.415 680.0423) 
(list 3839.4375 679.3923)))
(apply 'command (append '("pline") coords '("c")))
(setq currobj (ssadd (entlast) currobj))
(setq coords (list 
(list 3839.4375 679.2493) 
(list 3765.415 679.8993) 
(list 3765.415 679.7223) 
(list 3839.4375 679.1723)))
(apply 'command (append '("pline") coords '("c")))
(setq currobj (ssadd (entlast) currobj))
(setq coords (list 
(list 3839.4375 679.0293) 
(list 3765.415 679.5793) 
(list 3765.415 679.4023) 
(list 3839.4375 678.9523)))
(apply 'command (append '("pline") coords '("c")))
(setq currobj (ssadd (entlast) currobj))
(setq coords (list 
(list 3839.4375 678.8093) 
(list 3765.415 679.2593) 
(list 3765.415 679.0823) 
(list 3839.4375 678.7323)))
(apply 'command (append '("pline") coords '("c")))
(setq currobj (ssadd (entlast) currobj))
(setq coords (list 
(list 3839.4375 678.5893) 
(list 3765.415 678.9393) 
(list 3765.415 678.7623) 
(list 3839.4375 678.5123)))
(apply 'command (append '("pline") coords '("c")))
(setq currobj (ssadd (entlast) currobj))
(setq coords (list 
(list 3839.4375 678.3693) 
(list 3765.415 678.6193) 
(list 3765.415 678.4423) 
(list 3839.4375 678.2923)))
(apply 'command (append '("pline") coords '("c")))
(setq currobj (ssadd (entlast) currobj))
(setq coords (list 
(list 3839.4375 678.1493) 
(list 3765.415 678.2993) 
(list 3765.415 678.1223) 
(list 3839.4375 678.0723)))
(apply 'command (append '("pline") coords '("c")))
(setq currobj (ssadd (entlast) currobj))
(setq coords (list 
(list 3839.4375 677.9293) 
(list 3765.415 677.9793) 
(list 3765.415 677.8023) 
(list 3839.4375 677.8523)))
(apply 'command (append '("pline") coords '("c")))
(setq currobj (ssadd (entlast) currobj))
(setq coords (list 
(list 3839.4375 677.7093) 
(list 3765.415 677.6593) 
(list 3765.415 677.4823) 
(list 3839.4375 677.6323)))
(apply 'command (append '("pline") coords '("c")))
(setq currobj (ssadd (entlast) currobj))
(setq coords (list 
(list 3839.4375 677.4893) 
(list 3765.415 677.3393) 
(list 3765.415 677.1623) 
(list 3839.4375 677.4123)))
(apply 'command (append '("pline") coords '("c")))
(setq currobj (ssadd (entlast) currobj))
(setq coords (list 
(list 3839.4375 677.2693) 
(list 3765.415 677.0193) 
(list 3765.415 676.8423) 
(list 3839.4375 677.1923)))
(apply 'command (append '("pline") coords '("c")))
(setq currobj (ssadd (entlast) currobj))
(setq coords (list 
(list 3839.4375 677.0493) 
(list 3765.415 676.6993) 
(list 3765.415 676.5223) 
(list 3839.4375 676.9723)))
(apply 'command (append '("pline") coords '("c")))
(setq currobj (ssadd (entlast) currobj))
(setq coords (list 
(list 3839.4375 676.8293) 
(list 3765.415 676.3793) 
(list 3765.415 676.2023) 
(list 3839.4375 676.7523)))
(apply 'command (append '("pline") coords '("c")))
(setq currobj (ssadd (entlast) currobj))
(setq coords (list 
(list 3839.4375 676.6093) 
(list 3765.415 676.0593) 
(list 3765.415 675.8823) 
(list 3839.4375 676.5323)))
(apply 'command (append '("pline") coords '("c")))
(setq currobj (ssadd (entlast) currobj))
(setq coords (list 
(list 3839.4375 676.3893) 
(list 3765.415 675.7393) 
(list 3765.415 675.5623) 
(list 3839.4375 676.3123)))
(apply 'command (append '("pline") coords '("c")))
(setq currobj (ssadd (entlast) currobj))
(command "_layer" "set" "nitride" "")
(command "_layer" "set" "text" "")
(command "_circle" "3839.0625,665.1693" "0.075")
(command "_circle" "3839.0625,665.4693" "0.075")
(command "_circle" "3839.0625,665.7693" "0.075")
(command "_circle" "3839.0625,666.0693" "0.075")
(command "_circle" "3839.0625,666.3693" "0.075")
(command "_circle" "3838.7625,665.1693" "0.075")
(command "_circle" "3838.7625,665.4693" "0.075")
(command "_circle" "3838.7625,665.7693" "0.075")
(command "_circle" "3838.7625,666.0693" "0.075")
(command "_circle" "3838.7625,666.3693" "0.075")
(command "_circle" "3838.4625,665.1693" "0.075")
(command "_circle" "3838.4625,665.4693" "0.075")
(command "_circle" "3838.4625,665.7693" "0.075")
(command "_circle" "3838.4625,666.0693" "0.075")
(command "_circle" "3838.4625,666.3693" "0.075")
(command "_circle" "3838.1625,665.1693" "0.075")
(command "_circle" "3838.1625,665.4693" "0.075")
(command "_circle" "3838.1625,665.7693" "0.075")
(command "_circle" "3838.1625,666.0693" "0.075")
(command "_circle" "3838.1625,666.3693" "0.075")
(command "_circle" "3837.8625,665.1693" "0.075")
(command "_circle" "3837.8625,665.4693" "0.075")
(command "_circle" "3837.8625,665.7693" "0.075")
(command "_circle" "3837.8625,666.0693" "0.075")
(command "_circle" "3837.8625,666.3693" "0.075")
(command "_layer" "set" "nitride" "")
(setq coords (list 
(list 3840.2625 690.6123) 
(list 3840.2625 806.257) 
(list 3839.7375 806.257) 
(list 3839.7375 690.6123)))
(apply 'command (append '("pline") coords '("c")))
(setq currobj (ssadd (entlast) currobj))
(command "_layer" "set" "prebias" "")
(command "_rectangle" "3839.7375,690.6123" "3840.2625,806.257")
(setq currobj (ssadd (entlast) currobj))
(command "_layer" "set" "nitride" "")
(setq coords (list 
(list 3840.2625 806.257) 
(list 3840.5625 816.257) 
(list 3840.5625 816.257) 
(list 3840.5625 817.257) 
(list 3914.585 816.507) 
(list 3914.585 821.45) 
(list 3840.5625 820.7) 
(list 3840.5625 821.7) 
(list 3840.5625 821.7) 
(list 3840.2625 831.7) 
(list 3839.7375 831.7) 
(list 3839.4375 821.7) 
(list 3839.4375 821.7) 
(list 3839.4375 820.7) 
(list 3765.415 821.45) 
(list 3765.415 816.507) 
(list 3839.4375 817.257) 
(list 3839.4375 816.257) 
(list 3839.4375 816.257) 
(list 3839.7375 806.257)))
(apply 'command (append '("pline") coords '("c")))
(setq currobj (ssadd (entlast) currobj))
(command "_layer" "set" "prebias" "")
(setq coords (list 
(list 3839.4375 806.257) 
(list 3839.4375 817.257) 
(list 3765.415 816.507) 
(list 3765.415 821.45) 
(list 3839.4375 820.7) 
(list 3839.4375 831.7) 
(list 3840.5625 831.7) 
(list 3840.5625 820.7) 
(list 3914.585 821.45) 
(list 3914.585 816.507) 
(list 3840.5625 817.257) 
(list 3840.5625 806.257)))
(apply 'command (append '("pline") coords '("c")))
(setq currobj (ssadd (entlast) currobj))
(command "_layer" "set" "nitride" "")
(command "_layer" "set" "fda1" "")
(setq coords (list 
(list 3840.5625 817.4) 
(list 3914.585 816.65) 
(list 3914.585 816.827) 
(list 3840.5625 817.477)))
(apply 'command (append '("pline") coords '("c")))
(setq currobj (ssadd (entlast) currobj))
(setq coords (list 
(list 3840.5625 817.62) 
(list 3914.585 816.97) 
(list 3914.585 817.147) 
(list 3840.5625 817.697)))
(apply 'command (append '("pline") coords '("c")))
(setq currobj (ssadd (entlast) currobj))
(setq coords (list 
(list 3840.5625 817.84) 
(list 3914.585 817.29) 
(list 3914.585 817.467) 
(list 3840.5625 817.917)))
(apply 'command (append '("pline") coords '("c")))
(setq currobj (ssadd (entlast) currobj))
(setq coords (list 
(list 3840.5625 818.06) 
(list 3914.585 817.61) 
(list 3914.585 817.787) 
(list 3840.5625 818.137)))
(apply 'command (append '("pline") coords '("c")))
(setq currobj (ssadd (entlast) currobj))
(setq coords (list 
(list 3840.5625 818.28) 
(list 3914.585 817.93) 
(list 3914.585 818.107) 
(list 3840.5625 818.357)))
(apply 'command (append '("pline") coords '("c")))
(setq currobj (ssadd (entlast) currobj))
(setq coords (list 
(list 3840.5625 818.5) 
(list 3914.585 818.25) 
(list 3914.585 818.427) 
(list 3840.5625 818.577)))
(apply 'command (append '("pline") coords '("c")))
(setq currobj (ssadd (entlast) currobj))
(setq coords (list 
(list 3840.5625 818.72) 
(list 3914.585 818.57) 
(list 3914.585 818.747) 
(list 3840.5625 818.797)))
(apply 'command (append '("pline") coords '("c")))
(setq currobj (ssadd (entlast) currobj))
(setq coords (list 
(list 3840.5625 818.94) 
(list 3914.585 818.89) 
(list 3914.585 819.067) 
(list 3840.5625 819.017)))
(apply 'command (append '("pline") coords '("c")))
(setq currobj (ssadd (entlast) currobj))
(setq coords (list 
(list 3840.5625 819.16) 
(list 3914.585 819.21) 
(list 3914.585 819.387) 
(list 3840.5625 819.237)))
(apply 'command (append '("pline") coords '("c")))
(setq currobj (ssadd (entlast) currobj))
(setq coords (list 
(list 3840.5625 819.38) 
(list 3914.585 819.53) 
(list 3914.585 819.707) 
(list 3840.5625 819.457)))
(apply 'command (append '("pline") coords '("c")))
(setq currobj (ssadd (entlast) currobj))
(setq coords (list 
(list 3840.5625 819.6) 
(list 3914.585 819.85) 
(list 3914.585 820.027) 
(list 3840.5625 819.677)))
(apply 'command (append '("pline") coords '("c")))
(setq currobj (ssadd (entlast) currobj))
(setq coords (list 
(list 3840.5625 819.82) 
(list 3914.585 820.17) 
(list 3914.585 820.347) 
(list 3840.5625 819.897)))
(apply 'command (append '("pline") coords '("c")))
(setq currobj (ssadd (entlast) currobj))
(setq coords (list 
(list 3840.5625 820.04) 
(list 3914.585 820.49) 
(list 3914.585 820.667) 
(list 3840.5625 820.117)))
(apply 'command (append '("pline") coords '("c")))
(setq currobj (ssadd (entlast) currobj))
(setq coords (list 
(list 3840.5625 820.26) 
(list 3914.585 820.81) 
(list 3914.585 820.987) 
(list 3840.5625 820.337)))
(apply 'command (append '("pline") coords '("c")))
(setq currobj (ssadd (entlast) currobj))
(setq coords (list 
(list 3840.5625 820.48) 
(list 3914.585 821.13) 
(list 3914.585 821.307) 
(list 3840.5625 820.557)))
(apply 'command (append '("pline") coords '("c")))
(setq currobj (ssadd (entlast) currobj))
(setq coords (list 
(list 3839.4375 820.557) 
(list 3765.415 821.307) 
(list 3765.415 821.13) 
(list 3839.4375 820.48)))
(apply 'command (append '("pline") coords '("c")))
(setq currobj (ssadd (entlast) currobj))
(setq coords (list 
(list 3839.4375 820.337) 
(list 3765.415 820.987) 
(list 3765.415 820.81) 
(list 3839.4375 820.26)))
(apply 'command (append '("pline") coords '("c")))
(setq currobj (ssadd (entlast) currobj))
(setq coords (list 
(list 3839.4375 820.117) 
(list 3765.415 820.667) 
(list 3765.415 820.49) 
(list 3839.4375 820.04)))
(apply 'command (append '("pline") coords '("c")))
(setq currobj (ssadd (entlast) currobj))
(setq coords (list 
(list 3839.4375 819.897) 
(list 3765.415 820.347) 
(list 3765.415 820.17) 
(list 3839.4375 819.82)))
(apply 'command (append '("pline") coords '("c")))
(setq currobj (ssadd (entlast) currobj))
(setq coords (list 
(list 3839.4375 819.677) 
(list 3765.415 820.027) 
(list 3765.415 819.85) 
(list 3839.4375 819.6)))
(apply 'command (append '("pline") coords '("c")))
(setq currobj (ssadd (entlast) currobj))
(setq coords (list 
(list 3839.4375 819.457) 
(list 3765.415 819.707) 
(list 3765.415 819.53) 
(list 3839.4375 819.38)))
(apply 'command (append '("pline") coords '("c")))
(setq currobj (ssadd (entlast) currobj))
(setq coords (list 
(list 3839.4375 819.237) 
(list 3765.415 819.387) 
(list 3765.415 819.21) 
(list 3839.4375 819.16)))
(apply 'command (append '("pline") coords '("c")))
(setq currobj (ssadd (entlast) currobj))
(setq coords (list 
(list 3839.4375 819.017) 
(list 3765.415 819.067) 
(list 3765.415 818.89) 
(list 3839.4375 818.94)))
(apply 'command (append '("pline") coords '("c")))
(setq currobj (ssadd (entlast) currobj))
(setq coords (list 
(list 3839.4375 818.797) 
(list 3765.415 818.747) 
(list 3765.415 818.57) 
(list 3839.4375 818.72)))
(apply 'command (append '("pline") coords '("c")))
(setq currobj (ssadd (entlast) currobj))
(setq coords (list 
(list 3839.4375 818.577) 
(list 3765.415 818.427) 
(list 3765.415 818.25) 
(list 3839.4375 818.5)))
(apply 'command (append '("pline") coords '("c")))
(setq currobj (ssadd (entlast) currobj))
(setq coords (list 
(list 3839.4375 818.357) 
(list 3765.415 818.107) 
(list 3765.415 817.93) 
(list 3839.4375 818.28)))
(apply 'command (append '("pline") coords '("c")))
(setq currobj (ssadd (entlast) currobj))
(setq coords (list 
(list 3839.4375 818.137) 
(list 3765.415 817.787) 
(list 3765.415 817.61) 
(list 3839.4375 818.06)))
(apply 'command (append '("pline") coords '("c")))
(setq currobj (ssadd (entlast) currobj))
(setq coords (list 
(list 3839.4375 817.917) 
(list 3765.415 817.467) 
(list 3765.415 817.29) 
(list 3839.4375 817.84)))
(apply 'command (append '("pline") coords '("c")))
(setq currobj (ssadd (entlast) currobj))
(setq coords (list 
(list 3839.4375 817.697) 
(list 3765.415 817.147) 
(list 3765.415 816.97) 
(list 3839.4375 817.62)))
(apply 'command (append '("pline") coords '("c")))
(setq currobj (ssadd (entlast) currobj))
(setq coords (list 
(list 3839.4375 817.477) 
(list 3765.415 816.827) 
(list 3765.415 816.65) 
(list 3839.4375 817.4)))
(apply 'command (append '("pline") coords '("c")))
(setq currobj (ssadd (entlast) currobj))
(command "_layer" "set" "nitride" "")
(command "_layer" "set" "text" "")
(command "_circle" "3839.0625,806.257" "0.075")
(command "_circle" "3839.0625,806.557" "0.075")
(command "_circle" "3839.0625,806.857" "0.075")
(command "_circle" "3839.0625,807.157" "0.075")
(command "_circle" "3839.0625,807.457" "0.075")
(command "_circle" "3838.7625,806.257" "0.075")
(command "_circle" "3838.7625,806.557" "0.075")
(command "_circle" "3838.7625,806.857" "0.075")
(command "_circle" "3838.7625,807.157" "0.075")
(command "_circle" "3838.7625,807.457" "0.075")
(command "_circle" "3838.4625,806.257" "0.075")
(command "_circle" "3838.4625,806.557" "0.075")
(command "_circle" "3838.4625,806.857" "0.075")
(command "_circle" "3838.4625,807.157" "0.075")
(command "_circle" "3838.4625,807.457" "0.075")
(command "_circle" "3838.1625,806.257" "0.075")
(command "_circle" "3838.1625,806.557" "0.075")
(command "_circle" "3838.1625,806.857" "0.075")
(command "_circle" "3838.1625,807.157" "0.075")
(command "_circle" "3838.1625,807.457" "0.075")
(command "_circle" "3837.8625,806.257" "0.075")
(command "_circle" "3837.8625,806.557" "0.075")
(command "_circle" "3837.8625,806.857" "0.075")
(command "_circle" "3837.8625,807.157" "0.075")
(command "_circle" "3837.8625,807.457" "0.075")
(command "_layer" "set" "nitride" "")
(setq coords (list 
(list 3840.2625 831.7) 
(list 3840.2625 836.7) 
(list 3839.7375 836.7) 
(list 3839.7375 831.7)))
(apply 'command (append '("pline") coords '("c")))
(setq currobj (ssadd (entlast) currobj))
(command "_layer" "set" "prebias" "")
(command "_rectangle" "3839.7375,831.7" "3840.2625,836.7")
(setq currobj (ssadd (entlast) currobj))
(command "_layer" "set" "nitride" "")
(setq cooledsinglenanobeam12 currobj)
(setq currobj nil)
(setq currobj (ssadd))
; DRAWING PHOTONIC CRYSTAL
(command "_layer" "set" "negYjunc" "")
(setq coords (list 
(list 3840.135 866.7) 
(list 3840 851.7) 
(list 3840 866.7)))
(apply 'command (append '("pline") coords '("c")))
(setq currobj (ssadd (entlast) currobj))
(setq coords (list 
(list 3840.2625 836.7) 
(list 3840.415 866.7) 
(list 3841.116 866.7) 
(list 3841.116 836.7)))
(apply 'command (append '("pline") coords '("c")))
(setq currobj (ssadd (entlast) currobj))
(setq coords (list 
(list 3839.865 866.7) 
(list 3840 851.7) 
(list 3840 866.7)))
(apply 'command (append '("pline") coords '("c")))
(setq currobj (ssadd (entlast) currobj))
(setq coords (list 
(list 3839.7375 836.7) 
(list 3839.585 866.7) 
(list 3838.884 866.7) 
(list 3838.884 836.7)))
(apply 'command (append '("pline") coords '("c")))
(setq currobj (ssadd (entlast) currobj))
(command "_layer" "set" "nitride" "")
(setq yjunction12 currobj)
(setq currobj nil)
(setq currobj (ssadd))
(setq tap12 nil)
(setq tap12 (ssadd))
(command "_layer" "set" "phc" "")
(setq coords (list 
(list 3840 866.7) 
(list 3840.135 866.7) 
(list 3840.135 866.7103) 
(list 3840.135 866.7206) 
(list 3840.135 866.7308) 
(list 3840.135 866.7411) 
(list 3840.135 866.7514) 
(list 3840.135 866.7617) 
(list 3840.135 866.7719) 
(list 3840.135 866.7822) 
(list 3840.135 866.7925) 
(list 3840.135 866.8028) 
(list 3840.135 866.8131) 
(list 3840.135 866.8233) 
(list 3840.135 866.8336) 
(list 3840.135 866.8439) 
(list 3840.135 866.8542) 
(list 3840.135 866.8644) 
(list 3840.135 866.8747) 
(list 3840.135 866.885) 
(list 3840.135 866.8953) 
(list 3840.135 866.9056) 
(list 3840.135 866.9158) 
(list 3840.135 866.9261) 
(list 3840.135 866.9364) 
(list 3840.135 866.9467) 
(list 3840.135 866.9569) 
(list 3840.135 866.9672) 
(list 3840.135 866.9775) 
(list 3840.135 866.9878) 
(list 3840.135 866.9981) 
(list 3840.135 867.0083) 
(list 3840.135 867.0186) 
(list 3840.135 867.0289) 
(list 3840.135 867.0392) 
(list 3840.135 867.0494) 
(list 3840.135 867.0597) 
(list 3840.135 867.07) 
(list 3840 867.07)))
(apply 'command (append '("pline") coords '("c")))
(setq tap12 (ssadd (entlast) tap12))
(command "_mirror" (entlast) "" "3840,900" "3840,901" "No")
(setq tap12 (ssadd (entlast) tap12))
(setq coords (list 
(list 3840.4245 866.7) 
(list 3840.415 866.7) 
(list 3840.4153 866.7103) 
(list 3840.4155 866.7206) 
(list 3840.4157 866.7308) 
(list 3840.4158 866.7411) 
(list 3840.4159 866.7514) 
(list 3840.4158 866.7617) 
(list 3840.4157 866.7719) 
(list 3840.4154 866.7822) 
(list 3840.4151 866.7925) 
(list 3840.4147 866.8028) 
(list 3840.4142 866.8131) 
(list 3840.4136 866.8233) 
(list 3840.413 866.8336) 
(list 3840.4124 866.8439) 
(list 3840.4119 866.8542) 
(list 3840.4114 866.8644) 
(list 3840.4109 866.8747) 
(list 3840.4106 866.885) 
(list 3840.4105 866.8953) 
(list 3840.4105 866.9056) 
(list 3840.4106 866.9158) 
(list 3840.411 866.9261) 
(list 3840.4115 866.9364) 
(list 3840.4122 866.9467) 
(list 3840.4131 866.9569) 
(list 3840.4141 866.9672) 
(list 3840.4153 866.9775) 
(list 3840.4165 866.9878) 
(list 3840.4178 866.9981) 
(list 3840.4191 867.0083) 
(list 3840.4204 867.0186) 
(list 3840.4216 867.0289) 
(list 3840.4226 867.0392) 
(list 3840.4235 867.0494) 
(list 3840.4241 867.0597) 
(list 3840.4245 867.07) 
(list 3840.4245 867.07)))
(apply 'command (append '("pline") coords '("c")))
(setq tap12 (ssadd (entlast) tap12))
(command "_mirror" (entlast) "" "3840,900" "3840,901" "No")
(setq tap12 (ssadd (entlast) tap12))
(setq coords (list 
(list 3841.116 866.7) 
(list 3840.4245 866.7) 
(list 3840.4245 866.7103) 
(list 3840.4245 866.7206) 
(list 3840.4245 866.7308) 
(list 3840.4245 866.7411) 
(list 3840.4245 866.7514) 
(list 3840.4245 866.7617) 
(list 3840.4245 866.7719) 
(list 3840.4245 866.7822) 
(list 3840.4245 866.7925) 
(list 3840.4245 866.8028) 
(list 3840.4245 866.8131) 
(list 3840.4245 866.8233) 
(list 3840.4245 866.8336) 
(list 3840.4245 866.8439) 
(list 3840.4245 866.8542) 
(list 3840.4245 866.8644) 
(list 3840.4245 866.8747) 
(list 3840.4245 866.885) 
(list 3840.4245 866.8953) 
(list 3840.4245 866.9056) 
(list 3840.4245 866.9158) 
(list 3840.4245 866.9261) 
(list 3840.4245 866.9364) 
(list 3840.4245 866.9467) 
(list 3840.4245 866.9569) 
(list 3840.4245 866.9672) 
(list 3840.4245 866.9775) 
(list 3840.4245 866.9878) 
(list 3840.4245 866.9981) 
(list 3840.4245 867.0083) 
(list 3840.4245 867.0186) 
(list 3840.4245 867.0289) 
(list 3840.4245 867.0392) 
(list 3840.4245 867.0494) 
(list 3840.4245 867.0597) 
(list 3840.4245 867.07) 
(list 3841.116 867.07)))
(apply 'command (append '("pline") coords '("c")))
(setq tap12 (ssadd (entlast) tap12))
(command "_mirror" (entlast) "" "3840,900" "3840,901" "No")
(setq tap12 (ssadd (entlast) tap12))
(setq coords (list 
(list 3840 867.07) 
(list 3840.135 867.07) 
(list 3840.135 867.0803) 
(list 3840.135 867.0906) 
(list 3840.135 867.1008) 
(list 3840.135 867.1111) 
(list 3840.135 867.1214) 
(list 3840.135 867.1317) 
(list 3840.135 867.1419) 
(list 3840.135 867.1522) 
(list 3840.135 867.1625) 
(list 3840.135 867.1728) 
(list 3840.135 867.1831) 
(list 3840.135 867.1933) 
(list 3840.135 867.2036) 
(list 3840.135 867.2139) 
(list 3840.135 867.2242) 
(list 3840.135 867.2344) 
(list 3840.135 867.2447) 
(list 3840.135 867.255) 
(list 3840.135 867.2653) 
(list 3840.135 867.2756) 
(list 3840.135 867.2858) 
(list 3840.135 867.2961) 
(list 3840.135 867.3064) 
(list 3840.135 867.3167) 
(list 3840.135 867.3269) 
(list 3840.135 867.3372) 
(list 3840.135 867.3475) 
(list 3840.135 867.3578) 
(list 3840.135 867.3681) 
(list 3840.135 867.3783) 
(list 3840.135 867.3886) 
(list 3840.135 867.3989) 
(list 3840.135 867.4092) 
(list 3840.135 867.4194) 
(list 3840.135 867.4297) 
(list 3840.135 867.44) 
(list 3840 867.44)))
(apply 'command (append '("pline") coords '("c")))
(setq tap12 (ssadd (entlast) tap12))
(command "_mirror" (entlast) "" "3840,900" "3840,901" "No")
(setq tap12 (ssadd (entlast) tap12))
(setq coords (list 
(list 3840.4341 867.07) 
(list 3840.4245 867.07) 
(list 3840.4247 867.0803) 
(list 3840.4245 867.0906) 
(list 3840.424 867.1008) 
(list 3840.4232 867.1111) 
(list 3840.4221 867.1214) 
(list 3840.4208 867.1317) 
(list 3840.4192 867.1419) 
(list 3840.4174 867.1522) 
(list 3840.4155 867.1625) 
(list 3840.4135 867.1728) 
(list 3840.4114 867.1831) 
(list 3840.4094 867.1933) 
(list 3840.4076 867.2036) 
(list 3840.4058 867.2139) 
(list 3840.4044 867.2242) 
(list 3840.4032 867.2344) 
(list 3840.4023 867.2447) 
(list 3840.4019 867.255) 
(list 3840.4019 867.2653) 
(list 3840.4023 867.2756) 
(list 3840.4031 867.2858) 
(list 3840.4044 867.2961) 
(list 3840.406 867.3064) 
(list 3840.4081 867.3167) 
(list 3840.4104 867.3269) 
(list 3840.413 867.3372) 
(list 3840.4157 867.3475) 
(list 3840.4185 867.3578) 
(list 3840.4214 867.3681) 
(list 3840.4241 867.3783) 
(list 3840.4267 867.3886) 
(list 3840.429 867.3989) 
(list 3840.4309 867.4092) 
(list 3840.4325 867.4194) 
(list 3840.4335 867.4297) 
(list 3840.4341 867.44) 
(list 3840.4341 867.44)))
(apply 'command (append '("pline") coords '("c")))
(setq tap12 (ssadd (entlast) tap12))
(command "_mirror" (entlast) "" "3840,900" "3840,901" "No")
(setq tap12 (ssadd (entlast) tap12))
(setq coords (list 
(list 3841.116 867.07) 
(list 3840.4341 867.07) 
(list 3840.4341 867.0803) 
(list 3840.4341 867.0906) 
(list 3840.4341 867.1008) 
(list 3840.4341 867.1111) 
(list 3840.4341 867.1214) 
(list 3840.4341 867.1317) 
(list 3840.4341 867.1419) 
(list 3840.4341 867.1522) 
(list 3840.4341 867.1625) 
(list 3840.4341 867.1728) 
(list 3840.4341 867.1831) 
(list 3840.4341 867.1933) 
(list 3840.4341 867.2036) 
(list 3840.4341 867.2139) 
(list 3840.4341 867.2242) 
(list 3840.4341 867.2344) 
(list 3840.4341 867.2447) 
(list 3840.4341 867.255) 
(list 3840.4341 867.2653) 
(list 3840.4341 867.2756) 
(list 3840.4341 867.2858) 
(list 3840.4341 867.2961) 
(list 3840.4341 867.3064) 
(list 3840.4341 867.3167) 
(list 3840.4341 867.3269) 
(list 3840.4341 867.3372) 
(list 3840.4341 867.3475) 
(list 3840.4341 867.3578) 
(list 3840.4341 867.3681) 
(list 3840.4341 867.3783) 
(list 3840.4341 867.3886) 
(list 3840.4341 867.3989) 
(list 3840.4341 867.4092) 
(list 3840.4341 867.4194) 
(list 3840.4341 867.4297) 
(list 3840.4341 867.44) 
(list 3841.116 867.44)))
(apply 'command (append '("pline") coords '("c")))
(setq tap12 (ssadd (entlast) tap12))
(command "_mirror" (entlast) "" "3840,900" "3840,901" "No")
(setq tap12 (ssadd (entlast) tap12))
(setq coords (list 
(list 3840 867.44) 
(list 3840.135 867.44) 
(list 3840.135 867.4503) 
(list 3840.135 867.4606) 
(list 3840.135 867.4708) 
(list 3840.135 867.4811) 
(list 3840.135 867.4914) 
(list 3840.135 867.5017) 
(list 3840.135 867.5119) 
(list 3840.135 867.5222) 
(list 3840.135 867.5325) 
(list 3840.135 867.5428) 
(list 3840.135 867.5531) 
(list 3840.135 867.5633) 
(list 3840.135 867.5736) 
(list 3840.135 867.5839) 
(list 3840.135 867.5942) 
(list 3840.135 867.6044) 
(list 3840.135 867.6147) 
(list 3840.135 867.625) 
(list 3840.135 867.6353) 
(list 3840.135 867.6456) 
(list 3840.135 867.6558) 
(list 3840.135 867.6661) 
(list 3840.135 867.6764) 
(list 3840.135 867.6867) 
(list 3840.135 867.6969) 
(list 3840.135 867.7072) 
(list 3840.135 867.7175) 
(list 3840.135 867.7278) 
(list 3840.135 867.7381) 
(list 3840.135 867.7483) 
(list 3840.135 867.7586) 
(list 3840.135 867.7689) 
(list 3840.135 867.7792) 
(list 3840.135 867.7894) 
(list 3840.135 867.7997) 
(list 3840.135 867.81) 
(list 3840 867.81)))
(apply 'command (append '("pline") coords '("c")))
(setq tap12 (ssadd (entlast) tap12))
(command "_mirror" (entlast) "" "3840,900" "3840,901" "No")
(setq tap12 (ssadd (entlast) tap12))
(setq coords (list 
(list 3840.4436 867.44) 
(list 3840.4341 867.44) 
(list 3840.434 867.4503) 
(list 3840.4335 867.4606) 
(list 3840.4323 867.4708) 
(list 3840.4306 867.4811) 
(list 3840.4284 867.4914) 
(list 3840.4258 867.5017) 
(list 3840.4227 867.5119) 
(list 3840.4194 867.5222) 
(list 3840.4159 867.5325) 
(list 3840.4123 867.5428) 
(list 3840.4087 867.5531) 
(list 3840.4053 867.5633) 
(list 3840.4021 867.5736) 
(list 3840.3992 867.5839) 
(list 3840.3969 867.5942) 
(list 3840.395 867.6044) 
(list 3840.3938 867.6147) 
(list 3840.3932 867.625) 
(list 3840.3933 867.6353) 
(list 3840.3941 867.6456) 
(list 3840.3956 867.6558) 
(list 3840.3978 867.6661) 
(list 3840.4006 867.6764) 
(list 3840.4039 867.6867) 
(list 3840.4077 867.6969) 
(list 3840.4118 867.7072) 
(list 3840.4161 867.7175) 
(list 3840.4205 867.7278) 
(list 3840.4249 867.7381) 
(list 3840.4291 867.7483) 
(list 3840.4329 867.7586) 
(list 3840.4364 867.7689) 
(list 3840.4392 867.7792) 
(list 3840.4414 867.7894) 
(list 3840.4429 867.7997) 
(list 3840.4436 867.81) 
(list 3840.4436 867.81)))
(apply 'command (append '("pline") coords '("c")))
(setq tap12 (ssadd (entlast) tap12))
(command "_mirror" (entlast) "" "3840,900" "3840,901" "No")
(setq tap12 (ssadd (entlast) tap12))
(setq coords (list 
(list 3841.116 867.44) 
(list 3840.4436 867.44) 
(list 3840.4436 867.4503) 
(list 3840.4436 867.4606) 
(list 3840.4436 867.4708) 
(list 3840.4436 867.4811) 
(list 3840.4436 867.4914) 
(list 3840.4436 867.5017) 
(list 3840.4436 867.5119) 
(list 3840.4436 867.5222) 
(list 3840.4436 867.5325) 
(list 3840.4436 867.5428) 
(list 3840.4436 867.5531) 
(list 3840.4436 867.5633) 
(list 3840.4436 867.5736) 
(list 3840.4436 867.5839) 
(list 3840.4436 867.5942) 
(list 3840.4436 867.6044) 
(list 3840.4436 867.6147) 
(list 3840.4436 867.625) 
(list 3840.4436 867.6353) 
(list 3840.4436 867.6456) 
(list 3840.4436 867.6558) 
(list 3840.4436 867.6661) 
(list 3840.4436 867.6764) 
(list 3840.4436 867.6867) 
(list 3840.4436 867.6969) 
(list 3840.4436 867.7072) 
(list 3840.4436 867.7175) 
(list 3840.4436 867.7278) 
(list 3840.4436 867.7381) 
(list 3840.4436 867.7483) 
(list 3840.4436 867.7586) 
(list 3840.4436 867.7689) 
(list 3840.4436 867.7792) 
(list 3840.4436 867.7894) 
(list 3840.4436 867.7997) 
(list 3840.4436 867.81) 
(list 3841.116 867.81)))
(apply 'command (append '("pline") coords '("c")))
(setq tap12 (ssadd (entlast) tap12))
(command "_mirror" (entlast) "" "3840,900" "3840,901" "No")
(setq tap12 (ssadd (entlast) tap12))
(setq coords (list 
(list 3840 867.81) 
(list 3840.135 867.81) 
(list 3840.135 867.8203) 
(list 3840.135 867.8306) 
(list 3840.135 867.8408) 
(list 3840.135 867.8511) 
(list 3840.135 867.8614) 
(list 3840.135 867.8717) 
(list 3840.135 867.8819) 
(list 3840.135 867.8922) 
(list 3840.135 867.9025) 
(list 3840.135 867.9128) 
(list 3840.135 867.9231) 
(list 3840.135 867.9333) 
(list 3840.135 867.9436) 
(list 3840.135 867.9539) 
(list 3840.135 867.9642) 
(list 3840.135 867.9744) 
(list 3840.135 867.9847) 
(list 3840.135 867.995) 
(list 3840.135 868.0053) 
(list 3840.135 868.0156) 
(list 3840.135 868.0258) 
(list 3840.135 868.0361) 
(list 3840.135 868.0464) 
(list 3840.135 868.0567) 
(list 3840.135 868.0669) 
(list 3840.135 868.0772) 
(list 3840.135 868.0875) 
(list 3840.135 868.0978) 
(list 3840.135 868.1081) 
(list 3840.135 868.1183) 
(list 3840.135 868.1286) 
(list 3840.135 868.1389) 
(list 3840.135 868.1492) 
(list 3840.135 868.1594) 
(list 3840.135 868.1697) 
(list 3840.135 868.18) 
(list 3840 868.18)))
(apply 'command (append '("pline") coords '("c")))
(setq tap12 (ssadd (entlast) tap12))
(command "_mirror" (entlast) "" "3840,900" "3840,901" "No")
(setq tap12 (ssadd (entlast) tap12))
(setq coords (list 
(list 3840.4531 867.81) 
(list 3840.4436 867.81) 
(list 3840.4434 867.8203) 
(list 3840.4424 867.8306) 
(list 3840.4406 867.8408) 
(list 3840.438 867.8511) 
(list 3840.4347 867.8614) 
(list 3840.4307 867.8717) 
(list 3840.4263 867.8819) 
(list 3840.4214 867.8922) 
(list 3840.4163 867.9025) 
(list 3840.4111 867.9128) 
(list 3840.406 867.9231) 
(list 3840.4011 867.9333) 
(list 3840.3966 867.9436) 
(list 3840.3926 867.9539) 
(list 3840.3893 867.9642) 
(list 3840.3868 867.9744) 
(list 3840.3852 867.9847) 
(list 3840.3844 867.995) 
(list 3840.3847 868.0053) 
(list 3840.3859 868.0156) 
(list 3840.3881 868.0258) 
(list 3840.3912 868.0361) 
(list 3840.3951 868.0464) 
(list 3840.3997 868.0567) 
(list 3840.4049 868.0669) 
(list 3840.4106 868.0772) 
(list 3840.4165 868.0875) 
(list 3840.4225 868.0978) 
(list 3840.4284 868.1081) 
(list 3840.434 868.1183) 
(list 3840.4392 868.1286) 
(list 3840.4438 868.1389) 
(list 3840.4475 868.1492) 
(list 3840.4504 868.1594) 
(list 3840.4523 868.1697) 
(list 3840.4531 868.18) 
(list 3840.4531 868.18)))
(apply 'command (append '("pline") coords '("c")))
(setq tap12 (ssadd (entlast) tap12))
(command "_mirror" (entlast) "" "3840,900" "3840,901" "No")
(setq tap12 (ssadd (entlast) tap12))
(setq coords (list 
(list 3841.116 867.81) 
(list 3840.4531 867.81) 
(list 3840.4531 867.8203) 
(list 3840.4531 867.8306) 
(list 3840.4531 867.8408) 
(list 3840.4531 867.8511) 
(list 3840.4531 867.8614) 
(list 3840.4531 867.8717) 
(list 3840.4531 867.8819) 
(list 3840.4531 867.8922) 
(list 3840.4531 867.9025) 
(list 3840.4531 867.9128) 
(list 3840.4531 867.9231) 
(list 3840.4531 867.9333) 
(list 3840.4531 867.9436) 
(list 3840.4531 867.9539) 
(list 3840.4531 867.9642) 
(list 3840.4531 867.9744) 
(list 3840.4531 867.9847) 
(list 3840.4531 867.995) 
(list 3840.4531 868.0053) 
(list 3840.4531 868.0156) 
(list 3840.4531 868.0258) 
(list 3840.4531 868.0361) 
(list 3840.4531 868.0464) 
(list 3840.4531 868.0567) 
(list 3840.4531 868.0669) 
(list 3840.4531 868.0772) 
(list 3840.4531 868.0875) 
(list 3840.4531 868.0978) 
(list 3840.4531 868.1081) 
(list 3840.4531 868.1183) 
(list 3840.4531 868.1286) 
(list 3840.4531 868.1389) 
(list 3840.4531 868.1492) 
(list 3840.4531 868.1594) 
(list 3840.4531 868.1697) 
(list 3840.4531 868.18) 
(list 3841.116 868.18)))
(apply 'command (append '("pline") coords '("c")))
(setq tap12 (ssadd (entlast) tap12))
(command "_mirror" (entlast) "" "3840,900" "3840,901" "No")
(setq tap12 (ssadd (entlast) tap12))
(setq coords (list 
(list 3840 868.18) 
(list 3840.135 868.18) 
(list 3840.135 868.1903) 
(list 3840.135 868.2006) 
(list 3840.135 868.2108) 
(list 3840.135 868.2211) 
(list 3840.135 868.2314) 
(list 3840.135 868.2417) 
(list 3840.135 868.2519) 
(list 3840.135 868.2622) 
(list 3840.135 868.2725) 
(list 3840.135 868.2828) 
(list 3840.135 868.2931) 
(list 3840.135 868.3033) 
(list 3840.135 868.3136) 
(list 3840.135 868.3239) 
(list 3840.135 868.3342) 
(list 3840.135 868.3444) 
(list 3840.135 868.3547) 
(list 3840.135 868.365) 
(list 3840.135 868.3753) 
(list 3840.135 868.3856) 
(list 3840.135 868.3958) 
(list 3840.135 868.4061) 
(list 3840.135 868.4164) 
(list 3840.135 868.4267) 
(list 3840.135 868.4369) 
(list 3840.135 868.4472) 
(list 3840.135 868.4575) 
(list 3840.135 868.4678) 
(list 3840.135 868.4781) 
(list 3840.135 868.4883) 
(list 3840.135 868.4986) 
(list 3840.135 868.5089) 
(list 3840.135 868.5192) 
(list 3840.135 868.5294) 
(list 3840.135 868.5397) 
(list 3840.135 868.55) 
(list 3840 868.55)))
(apply 'command (append '("pline") coords '("c")))
(setq tap12 (ssadd (entlast) tap12))
(command "_mirror" (entlast) "" "3840,900" "3840,901" "No")
(setq tap12 (ssadd (entlast) tap12))
(setq coords (list 
(list 3840.4627 868.18) 
(list 3840.4531 868.18) 
(list 3840.4528 868.1903) 
(list 3840.4514 868.2006) 
(list 3840.4489 868.2108) 
(list 3840.4454 868.2211) 
(list 3840.441 868.2314) 
(list 3840.4357 868.2417) 
(list 3840.4298 868.2519) 
(list 3840.4234 868.2622) 
(list 3840.4167 868.2725) 
(list 3840.4099 868.2828) 
(list 3840.4033 868.2931) 
(list 3840.3969 868.3033) 
(list 3840.3911 868.3136) 
(list 3840.386 868.3239) 
(list 3840.3818 868.3342) 
(list 3840.3786 868.3444) 
(list 3840.3766 868.3547) 
(list 3840.3757 868.365) 
(list 3840.3761 868.3753) 
(list 3840.3777 868.3856) 
(list 3840.3806 868.3958) 
(list 3840.3846 868.4061) 
(list 3840.3896 868.4164) 
(list 3840.3956 868.4267) 
(list 3840.4022 868.4369) 
(list 3840.4094 868.4472) 
(list 3840.4169 868.4575) 
(list 3840.4245 868.4678) 
(list 3840.4319 868.4781) 
(list 3840.439 868.4883) 
(list 3840.4455 868.4986) 
(list 3840.4512 868.5089) 
(list 3840.4559 868.5192) 
(list 3840.4594 868.5294) 
(list 3840.4617 868.5397) 
(list 3840.4627 868.55) 
(list 3840.4627 868.55)))
(apply 'command (append '("pline") coords '("c")))
(setq tap12 (ssadd (entlast) tap12))
(command "_mirror" (entlast) "" "3840,900" "3840,901" "No")
(setq tap12 (ssadd (entlast) tap12))
(setq coords (list 
(list 3841.116 868.18) 
(list 3840.4627 868.18) 
(list 3840.4627 868.1903) 
(list 3840.4627 868.2006) 
(list 3840.4627 868.2108) 
(list 3840.4627 868.2211) 
(list 3840.4627 868.2314) 
(list 3840.4627 868.2417) 
(list 3840.4627 868.2519) 
(list 3840.4627 868.2622) 
(list 3840.4627 868.2725) 
(list 3840.4627 868.2828) 
(list 3840.4627 868.2931) 
(list 3840.4627 868.3033) 
(list 3840.4627 868.3136) 
(list 3840.4627 868.3239) 
(list 3840.4627 868.3342) 
(list 3840.4627 868.3444) 
(list 3840.4627 868.3547) 
(list 3840.4627 868.365) 
(list 3840.4627 868.3753) 
(list 3840.4627 868.3856) 
(list 3840.4627 868.3958) 
(list 3840.4627 868.4061) 
(list 3840.4627 868.4164) 
(list 3840.4627 868.4267) 
(list 3840.4627 868.4369) 
(list 3840.4627 868.4472) 
(list 3840.4627 868.4575) 
(list 3840.4627 868.4678) 
(list 3840.4627 868.4781) 
(list 3840.4627 868.4883) 
(list 3840.4627 868.4986) 
(list 3840.4627 868.5089) 
(list 3840.4627 868.5192) 
(list 3840.4627 868.5294) 
(list 3840.4627 868.5397) 
(list 3840.4627 868.55) 
(list 3841.116 868.55)))
(apply 'command (append '("pline") coords '("c")))
(setq tap12 (ssadd (entlast) tap12))
(command "_mirror" (entlast) "" "3840,900" "3840,901" "No")
(setq tap12 (ssadd (entlast) tap12))
(setq coords (list 
(list 3840 868.55) 
(list 3840.135 868.55) 
(list 3840.135 868.5603) 
(list 3840.135 868.5706) 
(list 3840.135 868.5808) 
(list 3840.135 868.5911) 
(list 3840.135 868.6014) 
(list 3840.135 868.6117) 
(list 3840.135 868.6219) 
(list 3840.135 868.6322) 
(list 3840.135 868.6425) 
(list 3840.135 868.6528) 
(list 3840.135 868.6631) 
(list 3840.135 868.6733) 
(list 3840.135 868.6836) 
(list 3840.135 868.6939) 
(list 3840.135 868.7042) 
(list 3840.135 868.7144) 
(list 3840.135 868.7247) 
(list 3840.135 868.735) 
(list 3840.135 868.7453) 
(list 3840.135 868.7556) 
(list 3840.135 868.7658) 
(list 3840.135 868.7761) 
(list 3840.135 868.7864) 
(list 3840.135 868.7967) 
(list 3840.135 868.8069) 
(list 3840.135 868.8172) 
(list 3840.135 868.8275) 
(list 3840.135 868.8378) 
(list 3840.135 868.8481) 
(list 3840.135 868.8583) 
(list 3840.135 868.8686) 
(list 3840.135 868.8789) 
(list 3840.135 868.8892) 
(list 3840.135 868.8994) 
(list 3840.135 868.9097) 
(list 3840.135 868.92) 
(list 3840 868.92)))
(apply 'command (append '("pline") coords '("c")))
(setq tap12 (ssadd (entlast) tap12))
(command "_mirror" (entlast) "" "3840,900" "3840,901" "No")
(setq tap12 (ssadd (entlast) tap12))
(setq coords (list 
(list 3840.4722 868.55) 
(list 3840.4627 868.55) 
(list 3840.4622 868.5603) 
(list 3840.4604 868.5706) 
(list 3840.4572 868.5808) 
(list 3840.4528 868.5911) 
(list 3840.4472 868.6014) 
(list 3840.4407 868.6117) 
(list 3840.4333 868.6219) 
(list 3840.4254 868.6322) 
(list 3840.4171 868.6425) 
(list 3840.4087 868.6528) 
(list 3840.4005 868.6631) 
(list 3840.3928 868.6733) 
(list 3840.3857 868.6836) 
(list 3840.3795 868.6939) 
(list 3840.3743 868.7042) 
(list 3840.3705 868.7144) 
(list 3840.368 868.7247) 
(list 3840.367 868.735) 
(list 3840.3675 868.7453) 
(list 3840.3695 868.7556) 
(list 3840.3731 868.7658) 
(list 3840.378 868.7761) 
(list 3840.3842 868.7864) 
(list 3840.3914 868.7967) 
(list 3840.3995 868.8069) 
(list 3840.4082 868.8172) 
(list 3840.4173 868.8275) 
(list 3840.4265 868.8378) 
(list 3840.4355 868.8481) 
(list 3840.444 868.8583) 
(list 3840.4518 868.8686) 
(list 3840.4586 868.8789) 
(list 3840.4642 868.8892) 
(list 3840.4684 868.8994) 
(list 3840.4711 868.9097) 
(list 3840.4722 868.92) 
(list 3840.4722 868.92)))
(apply 'command (append '("pline") coords '("c")))
(setq tap12 (ssadd (entlast) tap12))
(command "_mirror" (entlast) "" "3840,900" "3840,901" "No")
(setq tap12 (ssadd (entlast) tap12))
(setq coords (list 
(list 3841.116 868.55) 
(list 3840.4722 868.55) 
(list 3840.4722 868.5603) 
(list 3840.4722 868.5706) 
(list 3840.4722 868.5808) 
(list 3840.4722 868.5911) 
(list 3840.4722 868.6014) 
(list 3840.4722 868.6117) 
(list 3840.4722 868.6219) 
(list 3840.4722 868.6322) 
(list 3840.4722 868.6425) 
(list 3840.4722 868.6528) 
(list 3840.4722 868.6631) 
(list 3840.4722 868.6733) 
(list 3840.4722 868.6836) 
(list 3840.4722 868.6939) 
(list 3840.4722 868.7042) 
(list 3840.4722 868.7144) 
(list 3840.4722 868.7247) 
(list 3840.4722 868.735) 
(list 3840.4722 868.7453) 
(list 3840.4722 868.7556) 
(list 3840.4722 868.7658) 
(list 3840.4722 868.7761) 
(list 3840.4722 868.7864) 
(list 3840.4722 868.7967) 
(list 3840.4722 868.8069) 
(list 3840.4722 868.8172) 
(list 3840.4722 868.8275) 
(list 3840.4722 868.8378) 
(list 3840.4722 868.8481) 
(list 3840.4722 868.8583) 
(list 3840.4722 868.8686) 
(list 3840.4722 868.8789) 
(list 3840.4722 868.8892) 
(list 3840.4722 868.8994) 
(list 3840.4722 868.9097) 
(list 3840.4722 868.92) 
(list 3841.116 868.92)))
(apply 'command (append '("pline") coords '("c")))
(setq tap12 (ssadd (entlast) tap12))
(command "_mirror" (entlast) "" "3840,900" "3840,901" "No")
(setq tap12 (ssadd (entlast) tap12))
(setq coords (list 
(list 3840 868.92) 
(list 3840.135 868.92) 
(list 3840.135 868.9303) 
(list 3840.135 868.9406) 
(list 3840.135 868.9508) 
(list 3840.135 868.9611) 
(list 3840.135 868.9714) 
(list 3840.135 868.9817) 
(list 3840.135 868.9919) 
(list 3840.135 869.0022) 
(list 3840.135 869.0125) 
(list 3840.135 869.0228) 
(list 3840.135 869.0331) 
(list 3840.135 869.0433) 
(list 3840.135 869.0536) 
(list 3840.135 869.0639) 
(list 3840.135 869.0742) 
(list 3840.135 869.0844) 
(list 3840.135 869.0947) 
(list 3840.135 869.105) 
(list 3840.135 869.1153) 
(list 3840.135 869.1256) 
(list 3840.135 869.1358) 
(list 3840.135 869.1461) 
(list 3840.135 869.1564) 
(list 3840.135 869.1667) 
(list 3840.135 869.1769) 
(list 3840.135 869.1872) 
(list 3840.135 869.1975) 
(list 3840.135 869.2078) 
(list 3840.135 869.2181) 
(list 3840.135 869.2283) 
(list 3840.135 869.2386) 
(list 3840.135 869.2489) 
(list 3840.135 869.2592) 
(list 3840.135 869.2694) 
(list 3840.135 869.2797) 
(list 3840.135 869.29) 
(list 3840 869.29)))
(apply 'command (append '("pline") coords '("c")))
(setq tap12 (ssadd (entlast) tap12))
(command "_mirror" (entlast) "" "3840,900" "3840,901" "No")
(setq tap12 (ssadd (entlast) tap12))
(setq coords (list 
(list 3840.4817 868.92) 
(list 3840.4722 868.92) 
(list 3840.4716 868.9303) 
(list 3840.4694 868.9406) 
(list 3840.4655 868.9508) 
(list 3840.4602 868.9611) 
(list 3840.4535 868.9714) 
(list 3840.4456 868.9817) 
(list 3840.4368 868.9919) 
(list 3840.4274 869.0022) 
(list 3840.4175 869.0125) 
(list 3840.4076 869.0228) 
(list 3840.3978 869.0331) 
(list 3840.3886 869.0433) 
(list 3840.3802 869.0536) 
(list 3840.3729 869.0639) 
(list 3840.3668 869.0742) 
(list 3840.3623 869.0844) 
(list 3840.3594 869.0947) 
(list 3840.3582 869.105) 
(list 3840.3589 869.1153) 
(list 3840.3614 869.1256) 
(list 3840.3656 869.1358) 
(list 3840.3714 869.1461) 
(list 3840.3787 869.1564) 
(list 3840.3872 869.1667) 
(list 3840.3968 869.1769) 
(list 3840.407 869.1872) 
(list 3840.4177 869.1975) 
(list 3840.4285 869.2078) 
(list 3840.439 869.2181) 
(list 3840.4489 869.2283) 
(list 3840.458 869.2386) 
(list 3840.466 869.2489) 
(list 3840.4725 869.2592) 
(list 3840.4774 869.2694) 
(list 3840.4805 869.2797) 
(list 3840.4817 869.29) 
(list 3840.4817 869.29)))
(apply 'command (append '("pline") coords '("c")))
(setq tap12 (ssadd (entlast) tap12))
(command "_mirror" (entlast) "" "3840,900" "3840,901" "No")
(setq tap12 (ssadd (entlast) tap12))
(setq coords (list 
(list 3841.116 868.92) 
(list 3840.4817 868.92) 
(list 3840.4817 868.9303) 
(list 3840.4817 868.9406) 
(list 3840.4817 868.9508) 
(list 3840.4817 868.9611) 
(list 3840.4817 868.9714) 
(list 3840.4817 868.9817) 
(list 3840.4817 868.9919) 
(list 3840.4817 869.0022) 
(list 3840.4817 869.0125) 
(list 3840.4817 869.0228) 
(list 3840.4817 869.0331) 
(list 3840.4817 869.0433) 
(list 3840.4817 869.0536) 
(list 3840.4817 869.0639) 
(list 3840.4817 869.0742) 
(list 3840.4817 869.0844) 
(list 3840.4817 869.0947) 
(list 3840.4817 869.105) 
(list 3840.4817 869.1153) 
(list 3840.4817 869.1256) 
(list 3840.4817 869.1358) 
(list 3840.4817 869.1461) 
(list 3840.4817 869.1564) 
(list 3840.4817 869.1667) 
(list 3840.4817 869.1769) 
(list 3840.4817 869.1872) 
(list 3840.4817 869.1975) 
(list 3840.4817 869.2078) 
(list 3840.4817 869.2181) 
(list 3840.4817 869.2283) 
(list 3840.4817 869.2386) 
(list 3840.4817 869.2489) 
(list 3840.4817 869.2592) 
(list 3840.4817 869.2694) 
(list 3840.4817 869.2797) 
(list 3840.4817 869.29) 
(list 3841.116 869.29)))
(apply 'command (append '("pline") coords '("c")))
(setq tap12 (ssadd (entlast) tap12))
(command "_mirror" (entlast) "" "3840,900" "3840,901" "No")
(setq tap12 (ssadd (entlast) tap12))
(setq coords (list 
(list 3840 869.29) 
(list 3840.135 869.29) 
(list 3840.135 869.3003) 
(list 3840.135 869.3106) 
(list 3840.135 869.3208) 
(list 3840.135 869.3311) 
(list 3840.135 869.3414) 
(list 3840.135 869.3517) 
(list 3840.135 869.3619) 
(list 3840.135 869.3722) 
(list 3840.135 869.3825) 
(list 3840.135 869.3928) 
(list 3840.135 869.4031) 
(list 3840.135 869.4133) 
(list 3840.135 869.4236) 
(list 3840.135 869.4339) 
(list 3840.135 869.4442) 
(list 3840.135 869.4544) 
(list 3840.135 869.4647) 
(list 3840.135 869.475) 
(list 3840.135 869.4853) 
(list 3840.135 869.4956) 
(list 3840.135 869.5058) 
(list 3840.135 869.5161) 
(list 3840.135 869.5264) 
(list 3840.135 869.5367) 
(list 3840.135 869.5469) 
(list 3840.135 869.5572) 
(list 3840.135 869.5675) 
(list 3840.135 869.5778) 
(list 3840.135 869.5881) 
(list 3840.135 869.5983) 
(list 3840.135 869.6086) 
(list 3840.135 869.6189) 
(list 3840.135 869.6292) 
(list 3840.135 869.6394) 
(list 3840.135 869.6497) 
(list 3840.135 869.66) 
(list 3840 869.66)))
(apply 'command (append '("pline") coords '("c")))
(setq tap12 (ssadd (entlast) tap12))
(command "_mirror" (entlast) "" "3840,900" "3840,901" "No")
(setq tap12 (ssadd (entlast) tap12))
(setq coords (list 
(list 3840.4913 869.29) 
(list 3840.4817 869.29) 
(list 3840.481 869.3003) 
(list 3840.4784 869.3106) 
(list 3840.4739 869.3208) 
(list 3840.4676 869.3311) 
(list 3840.4598 869.3414) 
(list 3840.4506 869.3517) 
(list 3840.4404 869.3619) 
(list 3840.4293 869.3722) 
(list 3840.4179 869.3825) 
(list 3840.4064 869.3928) 
(list 3840.3951 869.4031) 
(list 3840.3844 869.4133) 
(list 3840.3747 869.4236) 
(list 3840.3663 869.4339) 
(list 3840.3593 869.4442) 
(list 3840.3541 869.4544) 
(list 3840.3508 869.4647) 
(list 3840.3495 869.475) 
(list 3840.3503 869.4853) 
(list 3840.3532 869.4956) 
(list 3840.3581 869.5058) 
(list 3840.3648 869.5161) 
(list 3840.3732 869.5264) 
(list 3840.3831 869.5367) 
(list 3840.394 869.5469) 
(list 3840.4058 869.5572) 
(list 3840.4181 869.5675) 
(list 3840.4304 869.5778) 
(list 3840.4425 869.5881) 
(list 3840.4539 869.5983) 
(list 3840.4643 869.6086) 
(list 3840.4734 869.6189) 
(list 3840.4808 869.6292) 
(list 3840.4864 869.6394) 
(list 3840.4899 869.6497) 
(list 3840.4913 869.66) 
(list 3840.4913 869.66)))
(apply 'command (append '("pline") coords '("c")))
(setq tap12 (ssadd (entlast) tap12))
(command "_mirror" (entlast) "" "3840,900" "3840,901" "No")
(setq tap12 (ssadd (entlast) tap12))
(setq coords (list 
(list 3841.116 869.29) 
(list 3840.4913 869.29) 
(list 3840.4913 869.3003) 
(list 3840.4913 869.3106) 
(list 3840.4913 869.3208) 
(list 3840.4913 869.3311) 
(list 3840.4913 869.3414) 
(list 3840.4913 869.3517) 
(list 3840.4913 869.3619) 
(list 3840.4913 869.3722) 
(list 3840.4913 869.3825) 
(list 3840.4913 869.3928) 
(list 3840.4913 869.4031) 
(list 3840.4913 869.4133) 
(list 3840.4913 869.4236) 
(list 3840.4913 869.4339) 
(list 3840.4913 869.4442) 
(list 3840.4913 869.4544) 
(list 3840.4913 869.4647) 
(list 3840.4913 869.475) 
(list 3840.4913 869.4853) 
(list 3840.4913 869.4956) 
(list 3840.4913 869.5058) 
(list 3840.4913 869.5161) 
(list 3840.4913 869.5264) 
(list 3840.4913 869.5367) 
(list 3840.4913 869.5469) 
(list 3840.4913 869.5572) 
(list 3840.4913 869.5675) 
(list 3840.4913 869.5778) 
(list 3840.4913 869.5881) 
(list 3840.4913 869.5983) 
(list 3840.4913 869.6086) 
(list 3840.4913 869.6189) 
(list 3840.4913 869.6292) 
(list 3840.4913 869.6394) 
(list 3840.4913 869.6497) 
(list 3840.4913 869.66) 
(list 3841.116 869.66)))
(apply 'command (append '("pline") coords '("c")))
(setq tap12 (ssadd (entlast) tap12))
(command "_mirror" (entlast) "" "3840,900" "3840,901" "No")
(setq tap12 (ssadd (entlast) tap12))
(setq coords (list 
(list 3840 869.66) 
(list 3840.135 869.66) 
(list 3840.135 869.6703) 
(list 3840.135 869.6806) 
(list 3840.135 869.6908) 
(list 3840.135 869.7011) 
(list 3840.135 869.7114) 
(list 3840.135 869.7217) 
(list 3840.135 869.7319) 
(list 3840.135 869.7422) 
(list 3840.135 869.7525) 
(list 3840.135 869.7628) 
(list 3840.135 869.7731) 
(list 3840.135 869.7833) 
(list 3840.135 869.7936) 
(list 3840.135 869.8039) 
(list 3840.135 869.8142) 
(list 3840.135 869.8244) 
(list 3840.135 869.8347) 
(list 3840.135 869.845) 
(list 3840.135 869.8553) 
(list 3840.135 869.8656) 
(list 3840.135 869.8758) 
(list 3840.135 869.8861) 
(list 3840.135 869.8964) 
(list 3840.135 869.9067) 
(list 3840.135 869.9169) 
(list 3840.135 869.9272) 
(list 3840.135 869.9375) 
(list 3840.135 869.9478) 
(list 3840.135 869.9581) 
(list 3840.135 869.9683) 
(list 3840.135 869.9786) 
(list 3840.135 869.9889) 
(list 3840.135 869.9992) 
(list 3840.135 870.0094) 
(list 3840.135 870.0197) 
(list 3840.135 870.03) 
(list 3840 870.03)))
(apply 'command (append '("pline") coords '("c")))
(setq tap12 (ssadd (entlast) tap12))
(command "_mirror" (entlast) "" "3840,900" "3840,901" "No")
(setq tap12 (ssadd (entlast) tap12))
(setq coords (list 
(list 3840.5008 869.66) 
(list 3840.4913 869.66) 
(list 3840.4904 869.6703) 
(list 3840.4874 869.6806) 
(list 3840.4822 869.6908) 
(list 3840.475 869.7011) 
(list 3840.466 869.7114) 
(list 3840.4556 869.7217) 
(list 3840.4439 869.7319) 
(list 3840.4313 869.7422) 
(list 3840.4183 869.7525) 
(list 3840.4052 869.7628) 
(list 3840.3924 869.7731) 
(list 3840.3803 869.7833) 
(list 3840.3693 869.7936) 
(list 3840.3597 869.8039) 
(list 3840.3518 869.8142) 
(list 3840.3459 869.8244) 
(list 3840.3422 869.8347) 
(list 3840.3408 869.845) 
(list 3840.3417 869.8553) 
(list 3840.345 869.8656) 
(list 3840.3505 869.8758) 
(list 3840.3582 869.8861) 
(list 3840.3677 869.8964) 
(list 3840.3789 869.9067) 
(list 3840.3913 869.9169) 
(list 3840.4047 869.9272) 
(list 3840.4185 869.9375) 
(list 3840.4324 869.9478) 
(list 3840.446 869.9581) 
(list 3840.4589 869.9683) 
(list 3840.4706 869.9786) 
(list 3840.4807 869.9889) 
(list 3840.4891 869.9992) 
(list 3840.4953 870.0094) 
(list 3840.4993 870.0197) 
(list 3840.5008 870.03) 
(list 3840.5008 870.03)))
(apply 'command (append '("pline") coords '("c")))
(setq tap12 (ssadd (entlast) tap12))
(command "_mirror" (entlast) "" "3840,900" "3840,901" "No")
(setq tap12 (ssadd (entlast) tap12))
(setq coords (list 
(list 3841.116 869.66) 
(list 3840.5008 869.66) 
(list 3840.5008 869.6703) 
(list 3840.5008 869.6806) 
(list 3840.5008 869.6908) 
(list 3840.5008 869.7011) 
(list 3840.5008 869.7114) 
(list 3840.5008 869.7217) 
(list 3840.5008 869.7319) 
(list 3840.5008 869.7422) 
(list 3840.5008 869.7525) 
(list 3840.5008 869.7628) 
(list 3840.5008 869.7731) 
(list 3840.5008 869.7833) 
(list 3840.5008 869.7936) 
(list 3840.5008 869.8039) 
(list 3840.5008 869.8142) 
(list 3840.5008 869.8244) 
(list 3840.5008 869.8347) 
(list 3840.5008 869.845) 
(list 3840.5008 869.8553) 
(list 3840.5008 869.8656) 
(list 3840.5008 869.8758) 
(list 3840.5008 869.8861) 
(list 3840.5008 869.8964) 
(list 3840.5008 869.9067) 
(list 3840.5008 869.9169) 
(list 3840.5008 869.9272) 
(list 3840.5008 869.9375) 
(list 3840.5008 869.9478) 
(list 3840.5008 869.9581) 
(list 3840.5008 869.9683) 
(list 3840.5008 869.9786) 
(list 3840.5008 869.9889) 
(list 3840.5008 869.9992) 
(list 3840.5008 870.0094) 
(list 3840.5008 870.0197) 
(list 3840.5008 870.03) 
(list 3841.116 870.03)))
(apply 'command (append '("pline") coords '("c")))
(setq tap12 (ssadd (entlast) tap12))
(command "_mirror" (entlast) "" "3840,900" "3840,901" "No")
(setq tap12 (ssadd (entlast) tap12))
(setq coords (list 
(list 3840 870.03) 
(list 3840.135 870.03) 
(list 3840.135 870.0403) 
(list 3840.135 870.0506) 
(list 3840.135 870.0608) 
(list 3840.135 870.0711) 
(list 3840.135 870.0814) 
(list 3840.135 870.0917) 
(list 3840.135 870.1019) 
(list 3840.135 870.1122) 
(list 3840.135 870.1225) 
(list 3840.135 870.1328) 
(list 3840.135 870.1431) 
(list 3840.135 870.1533) 
(list 3840.135 870.1636) 
(list 3840.135 870.1739) 
(list 3840.135 870.1842) 
(list 3840.135 870.1944) 
(list 3840.135 870.2047) 
(list 3840.135 870.215) 
(list 3840.135 870.2253) 
(list 3840.135 870.2356) 
(list 3840.135 870.2458) 
(list 3840.135 870.2561) 
(list 3840.135 870.2664) 
(list 3840.135 870.2767) 
(list 3840.135 870.2869) 
(list 3840.135 870.2972) 
(list 3840.135 870.3075) 
(list 3840.135 870.3178) 
(list 3840.135 870.3281) 
(list 3840.135 870.3383) 
(list 3840.135 870.3486) 
(list 3840.135 870.3589) 
(list 3840.135 870.3692) 
(list 3840.135 870.3794) 
(list 3840.135 870.3897) 
(list 3840.135 870.4) 
(list 3840 870.4)))
(apply 'command (append '("pline") coords '("c")))
(setq tap12 (ssadd (entlast) tap12))
(command "_mirror" (entlast) "" "3840,900" "3840,901" "No")
(setq tap12 (ssadd (entlast) tap12))
(setq coords (list 
(list 3840.5103 870.03) 
(list 3840.5008 870.03) 
(list 3840.4998 870.0403) 
(list 3840.4963 870.0506) 
(list 3840.4905 870.0608) 
(list 3840.4824 870.0711) 
(list 3840.4723 870.0814) 
(list 3840.4605 870.0917) 
(list 3840.4474 870.1019) 
(list 3840.4333 870.1122) 
(list 3840.4187 870.1225) 
(list 3840.404 870.1328) 
(list 3840.3897 870.1431) 
(list 3840.3761 870.1533) 
(list 3840.3638 870.1636) 
(list 3840.3531 870.1739) 
(list 3840.3443 870.1842) 
(list 3840.3377 870.1944) 
(list 3840.3336 870.2047) 
(list 3840.332 870.215) 
(list 3840.3331 870.2253) 
(list 3840.3368 870.2356) 
(list 3840.343 870.2458) 
(list 3840.3516 870.2561) 
(list 3840.3623 870.2664) 
(list 3840.3747 870.2767) 
(list 3840.3886 870.2869) 
(list 3840.4035 870.2972) 
(list 3840.4189 870.3075) 
(list 3840.4344 870.3178) 
(list 3840.4496 870.3281) 
(list 3840.4638 870.3383) 
(list 3840.4768 870.3486) 
(list 3840.4881 870.3589) 
(list 3840.4974 870.3692) 
(list 3840.5043 870.3794) 
(list 3840.5087 870.3897) 
(list 3840.5103 870.4) 
(list 3840.5103 870.4)))
(apply 'command (append '("pline") coords '("c")))
(setq tap12 (ssadd (entlast) tap12))
(command "_mirror" (entlast) "" "3840,900" "3840,901" "No")
(setq tap12 (ssadd (entlast) tap12))
(setq coords (list 
(list 3841.116 870.03) 
(list 3840.5103 870.03) 
(list 3840.5103 870.0403) 
(list 3840.5103 870.0506) 
(list 3840.5103 870.0608) 
(list 3840.5103 870.0711) 
(list 3840.5103 870.0814) 
(list 3840.5103 870.0917) 
(list 3840.5103 870.1019) 
(list 3840.5103 870.1122) 
(list 3840.5103 870.1225) 
(list 3840.5103 870.1328) 
(list 3840.5103 870.1431) 
(list 3840.5103 870.1533) 
(list 3840.5103 870.1636) 
(list 3840.5103 870.1739) 
(list 3840.5103 870.1842) 
(list 3840.5103 870.1944) 
(list 3840.5103 870.2047) 
(list 3840.5103 870.215) 
(list 3840.5103 870.2253) 
(list 3840.5103 870.2356) 
(list 3840.5103 870.2458) 
(list 3840.5103 870.2561) 
(list 3840.5103 870.2664) 
(list 3840.5103 870.2767) 
(list 3840.5103 870.2869) 
(list 3840.5103 870.2972) 
(list 3840.5103 870.3075) 
(list 3840.5103 870.3178) 
(list 3840.5103 870.3281) 
(list 3840.5103 870.3383) 
(list 3840.5103 870.3486) 
(list 3840.5103 870.3589) 
(list 3840.5103 870.3692) 
(list 3840.5103 870.3794) 
(list 3840.5103 870.3897) 
(list 3840.5103 870.4) 
(list 3841.116 870.4)))
(apply 'command (append '("pline") coords '("c")))
(setq tap12 (ssadd (entlast) tap12))
(command "_mirror" (entlast) "" "3840,900" "3840,901" "No")
(setq tap12 (ssadd (entlast) tap12))
(setq coords (list 
(list 3840 870.4) 
(list 3840.135 870.4) 
(list 3840.135 870.4103) 
(list 3840.135 870.4206) 
(list 3840.135 870.4308) 
(list 3840.135 870.4411) 
(list 3840.135 870.4514) 
(list 3840.135 870.4617) 
(list 3840.135 870.4719) 
(list 3840.135 870.4822) 
(list 3840.135 870.4925) 
(list 3840.135 870.5028) 
(list 3840.135 870.5131) 
(list 3840.135 870.5233) 
(list 3840.135 870.5336) 
(list 3840.135 870.5439) 
(list 3840.135 870.5542) 
(list 3840.135 870.5644) 
(list 3840.135 870.5747) 
(list 3840.135 870.585) 
(list 3840.135 870.5953) 
(list 3840.135 870.6056) 
(list 3840.135 870.6158) 
(list 3840.135 870.6261) 
(list 3840.135 870.6364) 
(list 3840.135 870.6467) 
(list 3840.135 870.6569) 
(list 3840.135 870.6672) 
(list 3840.135 870.6775) 
(list 3840.135 870.6878) 
(list 3840.135 870.6981) 
(list 3840.135 870.7083) 
(list 3840.135 870.7186) 
(list 3840.135 870.7289) 
(list 3840.135 870.7392) 
(list 3840.135 870.7494) 
(list 3840.135 870.7597) 
(list 3840.135 870.77) 
(list 3840 870.77)))
(apply 'command (append '("pline") coords '("c")))
(setq tap12 (ssadd (entlast) tap12))
(command "_mirror" (entlast) "" "3840,900" "3840,901" "No")
(setq tap12 (ssadd (entlast) tap12))
(setq coords (list 
(list 3840.5199 870.4) 
(list 3840.5103 870.4) 
(list 3840.5092 870.4103) 
(list 3840.5053 870.4206) 
(list 3840.4988 870.4308) 
(list 3840.4898 870.4411) 
(list 3840.4786 870.4514) 
(list 3840.4655 870.4617) 
(list 3840.4509 870.4719) 
(list 3840.4353 870.4822) 
(list 3840.4191 870.4925) 
(list 3840.4028 870.5028) 
(list 3840.3869 870.5131) 
(list 3840.3719 870.5233) 
(list 3840.3583 870.5336) 
(list 3840.3465 870.5439) 
(list 3840.3368 870.5542) 
(list 3840.3295 870.5644) 
(list 3840.325 870.5747) 
(list 3840.3233 870.585) 
(list 3840.3245 870.5953) 
(list 3840.3286 870.6056) 
(list 3840.3355 870.6158) 
(list 3840.345 870.6261) 
(list 3840.3568 870.6364) 
(list 3840.3706 870.6467) 
(list 3840.3859 870.6569) 
(list 3840.4023 870.6672) 
(list 3840.4193 870.6775) 
(list 3840.4364 870.6878) 
(list 3840.4531 870.6981) 
(list 3840.4688 870.7083) 
(list 3840.4831 870.7186) 
(list 3840.4955 870.7289) 
(list 3840.5057 870.7392) 
(list 3840.5133 870.7494) 
(list 3840.5181 870.7597) 
(list 3840.5199 870.77) 
(list 3840.5199 870.77)))
(apply 'command (append '("pline") coords '("c")))
(setq tap12 (ssadd (entlast) tap12))
(command "_mirror" (entlast) "" "3840,900" "3840,901" "No")
(setq tap12 (ssadd (entlast) tap12))
(setq coords (list 
(list 3841.116 870.4) 
(list 3840.5199 870.4) 
(list 3840.5199 870.4103) 
(list 3840.5199 870.4206) 
(list 3840.5199 870.4308) 
(list 3840.5199 870.4411) 
(list 3840.5199 870.4514) 
(list 3840.5199 870.4617) 
(list 3840.5199 870.4719) 
(list 3840.5199 870.4822) 
(list 3840.5199 870.4925) 
(list 3840.5199 870.5028) 
(list 3840.5199 870.5131) 
(list 3840.5199 870.5233) 
(list 3840.5199 870.5336) 
(list 3840.5199 870.5439) 
(list 3840.5199 870.5542) 
(list 3840.5199 870.5644) 
(list 3840.5199 870.5747) 
(list 3840.5199 870.585) 
(list 3840.5199 870.5953) 
(list 3840.5199 870.6056) 
(list 3840.5199 870.6158) 
(list 3840.5199 870.6261) 
(list 3840.5199 870.6364) 
(list 3840.5199 870.6467) 
(list 3840.5199 870.6569) 
(list 3840.5199 870.6672) 
(list 3840.5199 870.6775) 
(list 3840.5199 870.6878) 
(list 3840.5199 870.6981) 
(list 3840.5199 870.7083) 
(list 3840.5199 870.7186) 
(list 3840.5199 870.7289) 
(list 3840.5199 870.7392) 
(list 3840.5199 870.7494) 
(list 3840.5199 870.7597) 
(list 3840.5199 870.77) 
(list 3841.116 870.77)))
(apply 'command (append '("pline") coords '("c")))
(setq tap12 (ssadd (entlast) tap12))
(command "_mirror" (entlast) "" "3840,900" "3840,901" "No")
(setq tap12 (ssadd (entlast) tap12))
(setq coords (list 
(list 3840 870.77) 
(list 3840.135 870.77) 
(list 3840.135 870.7803) 
(list 3840.135 870.7906) 
(list 3840.135 870.8008) 
(list 3840.135 870.8111) 
(list 3840.135 870.8214) 
(list 3840.135 870.8317) 
(list 3840.135 870.8419) 
(list 3840.135 870.8522) 
(list 3840.135 870.8625) 
(list 3840.135 870.8728) 
(list 3840.135 870.8831) 
(list 3840.135 870.8933) 
(list 3840.135 870.9036) 
(list 3840.135 870.9139) 
(list 3840.135 870.9242) 
(list 3840.135 870.9344) 
(list 3840.135 870.9447) 
(list 3840.135 870.955) 
(list 3840.135 870.9653) 
(list 3840.135 870.9756) 
(list 3840.135 870.9858) 
(list 3840.135 870.9961) 
(list 3840.135 871.0064) 
(list 3840.135 871.0167) 
(list 3840.135 871.0269) 
(list 3840.135 871.0372) 
(list 3840.135 871.0475) 
(list 3840.135 871.0578) 
(list 3840.135 871.0681) 
(list 3840.135 871.0783) 
(list 3840.135 871.0886) 
(list 3840.135 871.0989) 
(list 3840.135 871.1092) 
(list 3840.135 871.1194) 
(list 3840.135 871.1297) 
(list 3840.135 871.14) 
(list 3840 871.14)))
(apply 'command (append '("pline") coords '("c")))
(setq tap12 (ssadd (entlast) tap12))
(command "_mirror" (entlast) "" "3840,900" "3840,901" "No")
(setq tap12 (ssadd (entlast) tap12))
(setq coords (list 
(list 3840.5294 870.77) 
(list 3840.5199 870.77) 
(list 3840.5186 870.7803) 
(list 3840.5143 870.7906) 
(list 3840.5071 870.8008) 
(list 3840.4972 870.8111) 
(list 3840.4848 870.8214) 
(list 3840.4705 870.8317) 
(list 3840.4544 870.8419) 
(list 3840.4373 870.8522) 
(list 3840.4195 870.8625) 
(list 3840.4016 870.8728) 
(list 3840.3842 870.8831) 
(list 3840.3678 870.8933) 
(list 3840.3528 870.9036) 
(list 3840.3399 870.9139) 
(list 3840.3293 870.9242) 
(list 3840.3214 870.9344) 
(list 3840.3164 870.9447) 
(list 3840.3146 870.955) 
(list 3840.3159 870.9653) 
(list 3840.3204 870.9756) 
(list 3840.328 870.9858) 
(list 3840.3384 870.9961) 
(list 3840.3513 871.0064) 
(list 3840.3664 871.0167) 
(list 3840.3831 871.0269) 
(list 3840.4011 871.0372) 
(list 3840.4197 871.0475) 
(list 3840.4384 871.0578) 
(list 3840.4566 871.0681) 
(list 3840.4738 871.0783) 
(list 3840.4894 871.0886) 
(list 3840.5029 871.0989) 
(list 3840.514 871.1092) 
(list 3840.5223 871.1194) 
(list 3840.5275 871.1297) 
(list 3840.5294 871.14) 
(list 3840.5294 871.14)))
(apply 'command (append '("pline") coords '("c")))
(setq tap12 (ssadd (entlast) tap12))
(command "_mirror" (entlast) "" "3840,900" "3840,901" "No")
(setq tap12 (ssadd (entlast) tap12))
(setq coords (list 
(list 3841.116 870.77) 
(list 3840.5294 870.77) 
(list 3840.5294 870.7803) 
(list 3840.5294 870.7906) 
(list 3840.5294 870.8008) 
(list 3840.5294 870.8111) 
(list 3840.5294 870.8214) 
(list 3840.5294 870.8317) 
(list 3840.5294 870.8419) 
(list 3840.5294 870.8522) 
(list 3840.5294 870.8625) 
(list 3840.5294 870.8728) 
(list 3840.5294 870.8831) 
(list 3840.5294 870.8933) 
(list 3840.5294 870.9036) 
(list 3840.5294 870.9139) 
(list 3840.5294 870.9242) 
(list 3840.5294 870.9344) 
(list 3840.5294 870.9447) 
(list 3840.5294 870.955) 
(list 3840.5294 870.9653) 
(list 3840.5294 870.9756) 
(list 3840.5294 870.9858) 
(list 3840.5294 870.9961) 
(list 3840.5294 871.0064) 
(list 3840.5294 871.0167) 
(list 3840.5294 871.0269) 
(list 3840.5294 871.0372) 
(list 3840.5294 871.0475) 
(list 3840.5294 871.0578) 
(list 3840.5294 871.0681) 
(list 3840.5294 871.0783) 
(list 3840.5294 871.0886) 
(list 3840.5294 871.0989) 
(list 3840.5294 871.1092) 
(list 3840.5294 871.1194) 
(list 3840.5294 871.1297) 
(list 3840.5294 871.14) 
(list 3841.116 871.14)))
(apply 'command (append '("pline") coords '("c")))
(setq tap12 (ssadd (entlast) tap12))
(command "_mirror" (entlast) "" "3840,900" "3840,901" "No")
(setq tap12 (ssadd (entlast) tap12))
(setq coords (list 
(list 3840 871.14) 
(list 3840.135 871.14) 
(list 3840.135 871.1503) 
(list 3840.135 871.1606) 
(list 3840.135 871.1708) 
(list 3840.135 871.1811) 
(list 3840.135 871.1914) 
(list 3840.135 871.2017) 
(list 3840.135 871.2119) 
(list 3840.135 871.2222) 
(list 3840.135 871.2325) 
(list 3840.135 871.2428) 
(list 3840.135 871.2531) 
(list 3840.135 871.2633) 
(list 3840.135 871.2736) 
(list 3840.135 871.2839) 
(list 3840.135 871.2942) 
(list 3840.135 871.3044) 
(list 3840.135 871.3147) 
(list 3840.135 871.325) 
(list 3840.135 871.3353) 
(list 3840.135 871.3456) 
(list 3840.135 871.3558) 
(list 3840.135 871.3661) 
(list 3840.135 871.3764) 
(list 3840.135 871.3867) 
(list 3840.135 871.3969) 
(list 3840.135 871.4072) 
(list 3840.135 871.4175) 
(list 3840.135 871.4278) 
(list 3840.135 871.4381) 
(list 3840.135 871.4483) 
(list 3840.135 871.4586) 
(list 3840.135 871.4689) 
(list 3840.135 871.4792) 
(list 3840.135 871.4894) 
(list 3840.135 871.4997) 
(list 3840.135 871.51) 
(list 3840 871.51)))
(apply 'command (append '("pline") coords '("c")))
(setq tap12 (ssadd (entlast) tap12))
(command "_mirror" (entlast) "" "3840,900" "3840,901" "No")
(setq tap12 (ssadd (entlast) tap12))
(setq coords (list 
(list 3840.5389 871.14) 
(list 3840.5294 871.14) 
(list 3840.528 871.1503) 
(list 3840.5233 871.1606) 
(list 3840.5154 871.1708) 
(list 3840.5046 871.1811) 
(list 3840.4911 871.1914) 
(list 3840.4754 871.2017) 
(list 3840.458 871.2119) 
(list 3840.4393 871.2222) 
(list 3840.4199 871.2325) 
(list 3840.4004 871.2428) 
(list 3840.3815 871.2531) 
(list 3840.3636 871.2633) 
(list 3840.3474 871.2736) 
(list 3840.3333 871.2839) 
(list 3840.3218 871.2942) 
(list 3840.3132 871.3044) 
(list 3840.3078 871.3147) 
(list 3840.3058 871.325) 
(list 3840.3073 871.3353) 
(list 3840.3123 871.3456) 
(list 3840.3205 871.3558) 
(list 3840.3318 871.3661) 
(list 3840.3459 871.3764) 
(list 3840.3622 871.3867) 
(list 3840.3804 871.3969) 
(list 3840.3999 871.4072) 
(list 3840.4201 871.4175) 
(list 3840.4404 871.4278) 
(list 3840.4601 871.4381) 
(list 3840.4787 871.4483) 
(list 3840.4956 871.4586) 
(list 3840.5103 871.4689) 
(list 3840.5223 871.4792) 
(list 3840.5313 871.4894) 
(list 3840.5369 871.4997) 
(list 3840.5389 871.51) 
(list 3840.5389 871.51)))
(apply 'command (append '("pline") coords '("c")))
(setq tap12 (ssadd (entlast) tap12))
(command "_mirror" (entlast) "" "3840,900" "3840,901" "No")
(setq tap12 (ssadd (entlast) tap12))
(setq coords (list 
(list 3841.116 871.14) 
(list 3840.5389 871.14) 
(list 3840.5389 871.1503) 
(list 3840.5389 871.1606) 
(list 3840.5389 871.1708) 
(list 3840.5389 871.1811) 
(list 3840.5389 871.1914) 
(list 3840.5389 871.2017) 
(list 3840.5389 871.2119) 
(list 3840.5389 871.2222) 
(list 3840.5389 871.2325) 
(list 3840.5389 871.2428) 
(list 3840.5389 871.2531) 
(list 3840.5389 871.2633) 
(list 3840.5389 871.2736) 
(list 3840.5389 871.2839) 
(list 3840.5389 871.2942) 
(list 3840.5389 871.3044) 
(list 3840.5389 871.3147) 
(list 3840.5389 871.325) 
(list 3840.5389 871.3353) 
(list 3840.5389 871.3456) 
(list 3840.5389 871.3558) 
(list 3840.5389 871.3661) 
(list 3840.5389 871.3764) 
(list 3840.5389 871.3867) 
(list 3840.5389 871.3969) 
(list 3840.5389 871.4072) 
(list 3840.5389 871.4175) 
(list 3840.5389 871.4278) 
(list 3840.5389 871.4381) 
(list 3840.5389 871.4483) 
(list 3840.5389 871.4586) 
(list 3840.5389 871.4689) 
(list 3840.5389 871.4792) 
(list 3840.5389 871.4894) 
(list 3840.5389 871.4997) 
(list 3840.5389 871.51) 
(list 3841.116 871.51)))
(apply 'command (append '("pline") coords '("c")))
(setq tap12 (ssadd (entlast) tap12))
(command "_mirror" (entlast) "" "3840,900" "3840,901" "No")
(setq tap12 (ssadd (entlast) tap12))
(setq coords (list 
(list 3840 871.51) 
(list 3840.135 871.51) 
(list 3840.135 871.5203) 
(list 3840.135 871.5306) 
(list 3840.135 871.5408) 
(list 3840.135 871.5511) 
(list 3840.135 871.5614) 
(list 3840.135 871.5717) 
(list 3840.135 871.5819) 
(list 3840.135 871.5922) 
(list 3840.135 871.6025) 
(list 3840.135 871.6128) 
(list 3840.135 871.6231) 
(list 3840.135 871.6333) 
(list 3840.135 871.6436) 
(list 3840.135 871.6539) 
(list 3840.135 871.6642) 
(list 3840.135 871.6744) 
(list 3840.135 871.6847) 
(list 3840.135 871.695) 
(list 3840.135 871.7053) 
(list 3840.135 871.7156) 
(list 3840.135 871.7258) 
(list 3840.135 871.7361) 
(list 3840.135 871.7464) 
(list 3840.135 871.7567) 
(list 3840.135 871.7669) 
(list 3840.135 871.7772) 
(list 3840.135 871.7875) 
(list 3840.135 871.7978) 
(list 3840.135 871.8081) 
(list 3840.135 871.8183) 
(list 3840.135 871.8286) 
(list 3840.135 871.8389) 
(list 3840.135 871.8492) 
(list 3840.135 871.8594) 
(list 3840.135 871.8697) 
(list 3840.135 871.88) 
(list 3840 871.88)))
(apply 'command (append '("pline") coords '("c")))
(setq tap12 (ssadd (entlast) tap12))
(command "_mirror" (entlast) "" "3840,900" "3840,901" "No")
(setq tap12 (ssadd (entlast) tap12))
(setq coords (list 
(list 3840.5485 871.51) 
(list 3840.5389 871.51) 
(list 3840.5374 871.5203) 
(list 3840.5323 871.5306) 
(list 3840.5237 871.5408) 
(list 3840.512 871.5511) 
(list 3840.4974 871.5614) 
(list 3840.4804 871.5717) 
(list 3840.4615 871.5819) 
(list 3840.4413 871.5922) 
(list 3840.4203 871.6025) 
(list 3840.3993 871.6128) 
(list 3840.3788 871.6231) 
(list 3840.3594 871.6333) 
(list 3840.3419 871.6436) 
(list 3840.3267 871.6539) 
(list 3840.3142 871.6642) 
(list 3840.305 871.6744) 
(list 3840.2992 871.6847) 
(list 3840.2971 871.695) 
(list 3840.2987 871.7053) 
(list 3840.3041 871.7156) 
(list 3840.313 871.7258) 
(list 3840.3252 871.7361) 
(list 3840.3404 871.7464) 
(list 3840.3581 871.7567) 
(list 3840.3777 871.7669) 
(list 3840.3987 871.7772) 
(list 3840.4205 871.7875) 
(list 3840.4424 871.7978) 
(list 3840.4636 871.8081) 
(list 3840.4837 871.8183) 
(list 3840.5019 871.8286) 
(list 3840.5177 871.8389) 
(list 3840.5306 871.8492) 
(list 3840.5403 871.8594) 
(list 3840.5463 871.8697) 
(list 3840.5485 871.88) 
(list 3840.5485 871.88)))
(apply 'command (append '("pline") coords '("c")))
(setq tap12 (ssadd (entlast) tap12))
(command "_mirror" (entlast) "" "3840,900" "3840,901" "No")
(setq tap12 (ssadd (entlast) tap12))
(setq coords (list 
(list 3841.116 871.51) 
(list 3840.5485 871.51) 
(list 3840.5485 871.5203) 
(list 3840.5485 871.5306) 
(list 3840.5485 871.5408) 
(list 3840.5485 871.5511) 
(list 3840.5485 871.5614) 
(list 3840.5485 871.5717) 
(list 3840.5485 871.5819) 
(list 3840.5485 871.5922) 
(list 3840.5485 871.6025) 
(list 3840.5485 871.6128) 
(list 3840.5485 871.6231) 
(list 3840.5485 871.6333) 
(list 3840.5485 871.6436) 
(list 3840.5485 871.6539) 
(list 3840.5485 871.6642) 
(list 3840.5485 871.6744) 
(list 3840.5485 871.6847) 
(list 3840.5485 871.695) 
(list 3840.5485 871.7053) 
(list 3840.5485 871.7156) 
(list 3840.5485 871.7258) 
(list 3840.5485 871.7361) 
(list 3840.5485 871.7464) 
(list 3840.5485 871.7567) 
(list 3840.5485 871.7669) 
(list 3840.5485 871.7772) 
(list 3840.5485 871.7875) 
(list 3840.5485 871.7978) 
(list 3840.5485 871.8081) 
(list 3840.5485 871.8183) 
(list 3840.5485 871.8286) 
(list 3840.5485 871.8389) 
(list 3840.5485 871.8492) 
(list 3840.5485 871.8594) 
(list 3840.5485 871.8697) 
(list 3840.5485 871.88) 
(list 3841.116 871.88)))
(apply 'command (append '("pline") coords '("c")))
(setq tap12 (ssadd (entlast) tap12))
(command "_mirror" (entlast) "" "3840,900" "3840,901" "No")
(setq tap12 (ssadd (entlast) tap12))
(setq coords (list 
(list 3840 871.88) 
(list 3840.135 871.88) 
(list 3840.135 871.8903) 
(list 3840.135 871.9006) 
(list 3840.135 871.9108) 
(list 3840.135 871.9211) 
(list 3840.135 871.9314) 
(list 3840.135 871.9417) 
(list 3840.135 871.9519) 
(list 3840.135 871.9622) 
(list 3840.135 871.9725) 
(list 3840.135 871.9828) 
(list 3840.135 871.9931) 
(list 3840.135 872.0033) 
(list 3840.135 872.0136) 
(list 3840.135 872.0239) 
(list 3840.135 872.0342) 
(list 3840.135 872.0444) 
(list 3840.135 872.0547) 
(list 3840.135 872.065) 
(list 3840.135 872.0753) 
(list 3840.135 872.0856) 
(list 3840.135 872.0958) 
(list 3840.135 872.1061) 
(list 3840.135 872.1164) 
(list 3840.135 872.1267) 
(list 3840.135 872.1369) 
(list 3840.135 872.1472) 
(list 3840.135 872.1575) 
(list 3840.135 872.1678) 
(list 3840.135 872.1781) 
(list 3840.135 872.1883) 
(list 3840.135 872.1986) 
(list 3840.135 872.2089) 
(list 3840.135 872.2192) 
(list 3840.135 872.2294) 
(list 3840.135 872.2397) 
(list 3840.135 872.25) 
(list 3840 872.25)))
(apply 'command (append '("pline") coords '("c")))
(setq tap12 (ssadd (entlast) tap12))
(command "_mirror" (entlast) "" "3840,900" "3840,901" "No")
(setq tap12 (ssadd (entlast) tap12))
(setq coords (list 
(list 3840.558 871.88) 
(list 3840.5485 871.88) 
(list 3840.5468 871.8903) 
(list 3840.5413 871.9006) 
(list 3840.532 871.9108) 
(list 3840.5194 871.9211) 
(list 3840.5037 871.9314) 
(list 3840.4854 871.9417) 
(list 3840.465 871.9519) 
(list 3840.4432 871.9622) 
(list 3840.4207 871.9725) 
(list 3840.3981 871.9828) 
(list 3840.376 871.9931) 
(list 3840.3553 872.0033) 
(list 3840.3364 872.0136) 
(list 3840.3201 872.0239) 
(list 3840.3067 872.0342) 
(list 3840.2968 872.0444) 
(list 3840.2906 872.0547) 
(list 3840.2884 872.065) 
(list 3840.2901 872.0753) 
(list 3840.2959 872.0856) 
(list 3840.3055 872.0958) 
(list 3840.3186 872.1061) 
(list 3840.3349 872.1164) 
(list 3840.3539 872.1267) 
(list 3840.375 872.1369) 
(list 3840.3975 872.1472) 
(list 3840.4209 872.1575) 
(list 3840.4443 872.1678) 
(list 3840.4672 872.1781) 
(list 3840.4887 872.1883) 
(list 3840.5082 872.1986) 
(list 3840.5251 872.2089) 
(list 3840.539 872.2192) 
(list 3840.5492 872.2294) 
(list 3840.5557 872.2397) 
(list 3840.558 872.25) 
(list 3840.558 872.25)))
(apply 'command (append '("pline") coords '("c")))
(setq tap12 (ssadd (entlast) tap12))
(command "_mirror" (entlast) "" "3840,900" "3840,901" "No")
(setq tap12 (ssadd (entlast) tap12))
(setq coords (list 
(list 3841.116 871.88) 
(list 3840.558 871.88) 
(list 3840.558 871.8903) 
(list 3840.558 871.9006) 
(list 3840.558 871.9108) 
(list 3840.558 871.9211) 
(list 3840.558 871.9314) 
(list 3840.558 871.9417) 
(list 3840.558 871.9519) 
(list 3840.558 871.9622) 
(list 3840.558 871.9725) 
(list 3840.558 871.9828) 
(list 3840.558 871.9931) 
(list 3840.558 872.0033) 
(list 3840.558 872.0136) 
(list 3840.558 872.0239) 
(list 3840.558 872.0342) 
(list 3840.558 872.0444) 
(list 3840.558 872.0547) 
(list 3840.558 872.065) 
(list 3840.558 872.0753) 
(list 3840.558 872.0856) 
(list 3840.558 872.0958) 
(list 3840.558 872.1061) 
(list 3840.558 872.1164) 
(list 3840.558 872.1267) 
(list 3840.558 872.1369) 
(list 3840.558 872.1472) 
(list 3840.558 872.1575) 
(list 3840.558 872.1678) 
(list 3840.558 872.1781) 
(list 3840.558 872.1883) 
(list 3840.558 872.1986) 
(list 3840.558 872.2089) 
(list 3840.558 872.2192) 
(list 3840.558 872.2294) 
(list 3840.558 872.2397) 
(list 3840.558 872.25) 
(list 3841.116 872.25)))
(apply 'command (append '("pline") coords '("c")))
(setq tap12 (ssadd (entlast) tap12))
(command "_mirror" (entlast) "" "3840,900" "3840,901" "No")
(setq tap12 (ssadd (entlast) tap12))
(command "_block" "blktap12" "3840,900" tap12 "")
(command "_insert" "blktap12" "3840,900" "1" "1" "0")
(command "_insert" "blktap12" "3840,900" "1" "1" "180")
(setq uc12 nil)
(setq uc12 (ssadd))
(setq coords (list 
(list 0 -0.185) 
(list 0.135 -0.185) 
(list 0.135 -0.17472) 
(list 0.135 -0.16444) 
(list 0.135 -0.15417) 
(list 0.135 -0.14389) 
(list 0.135 -0.13361) 
(list 0.135 -0.12333) 
(list 0.135 -0.11306) 
(list 0.135 -0.10278) 
(list 0.135 -0.0925) 
(list 0.135 -0.082222) 
(list 0.135 -0.071944) 
(list 0.135 -0.061667) 
(list 0.135 -0.051389) 
(list 0.135 -0.041111) 
(list 0.135 -0.030833) 
(list 0.135 -0.020556) 
(list 0.135 -0.010278) 
(list 0.135 0) 
(list 0.135 0.010278) 
(list 0.135 0.020556) 
(list 0.135 0.030833) 
(list 0.135 0.041111) 
(list 0.135 0.051389) 
(list 0.135 0.061667) 
(list 0.135 0.071944) 
(list 0.135 0.082222) 
(list 0.135 0.0925) 
(list 0.135 0.10278) 
(list 0.135 0.11306) 
(list 0.135 0.12333) 
(list 0.135 0.13361) 
(list 0.135 0.14389) 
(list 0.135 0.15417) 
(list 0.135 0.16444) 
(list 0.135 0.17472) 
(list 0.135 0.185) 
(list 0 0.185)))
(apply 'command (append '("pline") coords '("c")))
(setq uc12 (ssadd (entlast) uc12))
(setq coords (list 
(list 1.116 -0.185) 
(list 0.558 -0.185) 
(list 0.55592 -0.17472) 
(list 0.54974 -0.16444) 
(list 0.53965 -0.15417) 
(list 0.52595 -0.14389) 
(list 0.50906 -0.13361) 
(list 0.4895 -0.12333) 
(list 0.46786 -0.11306) 
(list 0.44479 -0.10278) 
(list 0.421 -0.0925) 
(list 0.39721 -0.082222) 
(list 0.37414 -0.071944) 
(list 0.3525 -0.061667) 
(list 0.33294 -0.051389) 
(list 0.31605 -0.041111) 
(list 0.30235 -0.030833) 
(list 0.29226 -0.020556) 
(list 0.28608 -0.010278) 
(list 0.284 0) 
(list 0.28608 0.010278) 
(list 0.29226 0.020556) 
(list 0.30235 0.030833) 
(list 0.31605 0.041111) 
(list 0.33294 0.051389) 
(list 0.3525 0.061667) 
(list 0.37414 0.071944) 
(list 0.39721 0.082222) 
(list 0.421 0.0925) 
(list 0.44479 0.10278) 
(list 0.46786 0.11306) 
(list 0.4895 0.12333) 
(list 0.50906 0.13361) 
(list 0.52595 0.14389) 
(list 0.53965 0.15417) 
(list 0.54974 0.16444) 
(list 0.55592 0.17472) 
(list 0.558 0.185) 
(list 1.116 0.185)))
(apply 'command (append '("pline") coords '("c")))
(setq uc12 (ssadd (entlast) uc12))
(command "_block" "blkuc12" "0,0.185" uc12 "")
(command "_insert" "blkuc12" "3840,872.62" "1" "1" "0")
(command "_insert" "blkuc12" "3840,872.25" "1" "1" "180")
(command "_insert" "blkuc12" "3840,872.99" "1" "1" "0")
(command "_insert" "blkuc12" "3840,872.62" "1" "1" "180")
(command "_insert" "blkuc12" "3840,873.36" "1" "1" "0")
(command "_insert" "blkuc12" "3840,872.99" "1" "1" "180")
(command "_insert" "blkuc12" "3840,873.73" "1" "1" "0")
(command "_insert" "blkuc12" "3840,873.36" "1" "1" "180")
(command "_insert" "blkuc12" "3840,874.1" "1" "1" "0")
(command "_insert" "blkuc12" "3840,873.73" "1" "1" "180")
(command "_insert" "blkuc12" "3840,874.47" "1" "1" "0")
(command "_insert" "blkuc12" "3840,874.1" "1" "1" "180")
(command "_insert" "blkuc12" "3840,874.84" "1" "1" "0")
(command "_insert" "blkuc12" "3840,874.47" "1" "1" "180")
(command "_insert" "blkuc12" "3840,875.21" "1" "1" "0")
(command "_insert" "blkuc12" "3840,874.84" "1" "1" "180")
(command "_insert" "blkuc12" "3840,875.58" "1" "1" "0")
(command "_insert" "blkuc12" "3840,875.21" "1" "1" "180")
(command "_insert" "blkuc12" "3840,875.95" "1" "1" "0")
(command "_insert" "blkuc12" "3840,875.58" "1" "1" "180")
(command "_insert" "blkuc12" "3840,876.32" "1" "1" "0")
(command "_insert" "blkuc12" "3840,875.95" "1" "1" "180")
(command "_insert" "blkuc12" "3840,876.69" "1" "1" "0")
(command "_insert" "blkuc12" "3840,876.32" "1" "1" "180")
(command "_insert" "blkuc12" "3840,877.06" "1" "1" "0")
(command "_insert" "blkuc12" "3840,876.69" "1" "1" "180")
(command "_insert" "blkuc12" "3840,877.43" "1" "1" "0")
(command "_insert" "blkuc12" "3840,877.06" "1" "1" "180")
(command "_insert" "blkuc12" "3840,877.8" "1" "1" "0")
(command "_insert" "blkuc12" "3840,877.43" "1" "1" "180")
(command "_insert" "blkuc12" "3840,878.17" "1" "1" "0")
(command "_insert" "blkuc12" "3840,877.8" "1" "1" "180")
(command "_insert" "blkuc12" "3840,878.54" "1" "1" "0")
(command "_insert" "blkuc12" "3840,878.17" "1" "1" "180")
(command "_insert" "blkuc12" "3840,878.91" "1" "1" "0")
(command "_insert" "blkuc12" "3840,878.54" "1" "1" "180")
(command "_insert" "blkuc12" "3840,879.28" "1" "1" "0")
(command "_insert" "blkuc12" "3840,878.91" "1" "1" "180")
(command "_insert" "blkuc12" "3840,879.65" "1" "1" "0")
(command "_insert" "blkuc12" "3840,879.28" "1" "1" "180")
(command "_insert" "blkuc12" "3840,880.02" "1" "1" "0")
(command "_insert" "blkuc12" "3840,879.65" "1" "1" "180")
(command "_insert" "blkuc12" "3840,880.39" "1" "1" "0")
(command "_insert" "blkuc12" "3840,880.02" "1" "1" "180")
(command "_insert" "blkuc12" "3840,880.76" "1" "1" "0")
(command "_insert" "blkuc12" "3840,880.39" "1" "1" "180")
(command "_insert" "blkuc12" "3840,881.13" "1" "1" "0")
(command "_insert" "blkuc12" "3840,880.76" "1" "1" "180")
(command "_insert" "blkuc12" "3840,881.5" "1" "1" "0")
(command "_insert" "blkuc12" "3840,881.13" "1" "1" "180")
(command "_insert" "blkuc12" "3840,881.87" "1" "1" "0")
(command "_insert" "blkuc12" "3840,881.5" "1" "1" "180")
(command "_insert" "blkuc12" "3840,882.24" "1" "1" "0")
(command "_insert" "blkuc12" "3840,881.87" "1" "1" "180")
(command "_insert" "blkuc12" "3840,882.61" "1" "1" "0")
(command "_insert" "blkuc12" "3840,882.24" "1" "1" "180")
(command "_insert" "blkuc12" "3840,882.98" "1" "1" "0")
(command "_insert" "blkuc12" "3840,882.61" "1" "1" "180")
(command "_insert" "blkuc12" "3840,883.35" "1" "1" "0")
(command "_insert" "blkuc12" "3840,882.98" "1" "1" "180")
(command "_insert" "blkuc12" "3840,883.72" "1" "1" "0")
(command "_insert" "blkuc12" "3840,883.35" "1" "1" "180")
(command "_insert" "blkuc12" "3840,884.09" "1" "1" "0")
(command "_insert" "blkuc12" "3840,883.72" "1" "1" "180")
(command "_insert" "blkuc12" "3840,884.46" "1" "1" "0")
(command "_insert" "blkuc12" "3840,884.09" "1" "1" "180")
(command "_insert" "blkuc12" "3840,884.83" "1" "1" "0")
(command "_insert" "blkuc12" "3840,884.46" "1" "1" "180")
(command "_insert" "blkuc12" "3840,885.2" "1" "1" "0")
(command "_insert" "blkuc12" "3840,884.83" "1" "1" "180")
(command "_insert" "blkuc12" "3840,885.57" "1" "1" "0")
(command "_insert" "blkuc12" "3840,885.2" "1" "1" "180")
(command "_insert" "blkuc12" "3840,885.94" "1" "1" "0")
(command "_insert" "blkuc12" "3840,885.57" "1" "1" "180")
(command "_insert" "blkuc12" "3840,886.31" "1" "1" "0")
(command "_insert" "blkuc12" "3840,885.94" "1" "1" "180")
(command "_insert" "blkuc12" "3840,886.68" "1" "1" "0")
(command "_insert" "blkuc12" "3840,886.31" "1" "1" "180")
(command "_insert" "blkuc12" "3840,887.05" "1" "1" "0")
(command "_insert" "blkuc12" "3840,886.68" "1" "1" "180")
(command "_insert" "blkuc12" "3840,887.42" "1" "1" "0")
(command "_insert" "blkuc12" "3840,887.05" "1" "1" "180")
(command "_insert" "blkuc12" "3840,887.79" "1" "1" "0")
(command "_insert" "blkuc12" "3840,887.42" "1" "1" "180")
(command "_insert" "blkuc12" "3840,888.16" "1" "1" "0")
(command "_insert" "blkuc12" "3840,887.79" "1" "1" "180")
(command "_insert" "blkuc12" "3840,888.53" "1" "1" "0")
(command "_insert" "blkuc12" "3840,888.16" "1" "1" "180")
(command "_insert" "blkuc12" "3840,888.9" "1" "1" "0")
(command "_insert" "blkuc12" "3840,888.53" "1" "1" "180")
(command "_insert" "blkuc12" "3840,889.27" "1" "1" "0")
(command "_insert" "blkuc12" "3840,888.9" "1" "1" "180")
(command "_insert" "blkuc12" "3840,889.64" "1" "1" "0")
(command "_insert" "blkuc12" "3840,889.27" "1" "1" "180")
(command "_insert" "blkuc12" "3840,890.01" "1" "1" "0")
(command "_insert" "blkuc12" "3840,889.64" "1" "1" "180")
(command "_insert" "blkuc12" "3840,890.38" "1" "1" "0")
(command "_insert" "blkuc12" "3840,890.01" "1" "1" "180")
(command "_insert" "blkuc12" "3840,890.75" "1" "1" "0")
(command "_insert" "blkuc12" "3840,890.38" "1" "1" "180")
(command "_insert" "blkuc12" "3840,891.12" "1" "1" "0")
(command "_insert" "blkuc12" "3840,890.75" "1" "1" "180")
(command "_insert" "blkuc12" "3840,891.49" "1" "1" "0")
(command "_insert" "blkuc12" "3840,891.12" "1" "1" "180")
(command "_insert" "blkuc12" "3840,891.86" "1" "1" "0")
(command "_insert" "blkuc12" "3840,891.49" "1" "1" "180")
(command "_insert" "blkuc12" "3840,892.23" "1" "1" "0")
(command "_insert" "blkuc12" "3840,891.86" "1" "1" "180")
(command "_insert" "blkuc12" "3840,892.6" "1" "1" "0")
(command "_insert" "blkuc12" "3840,892.23" "1" "1" "180")
(command "_insert" "blkuc12" "3840,892.97" "1" "1" "0")
(command "_insert" "blkuc12" "3840,892.6" "1" "1" "180")
(command "_insert" "blkuc12" "3840,893.34" "1" "1" "0")
(command "_insert" "blkuc12" "3840,892.97" "1" "1" "180")
(command "_insert" "blkuc12" "3840,893.71" "1" "1" "0")
(command "_insert" "blkuc12" "3840,893.34" "1" "1" "180")
(command "_insert" "blkuc12" "3840,894.08" "1" "1" "0")
(command "_insert" "blkuc12" "3840,893.71" "1" "1" "180")
(command "_insert" "blkuc12" "3840,894.45" "1" "1" "0")
(command "_insert" "blkuc12" "3840,894.08" "1" "1" "180")
(command "_insert" "blkuc12" "3840,894.82" "1" "1" "0")
(command "_insert" "blkuc12" "3840,894.45" "1" "1" "180")
(command "_insert" "blkuc12" "3840,895.19" "1" "1" "0")
(command "_insert" "blkuc12" "3840,894.82" "1" "1" "180")
(command "_insert" "blkuc12" "3840,895.56" "1" "1" "0")
(command "_insert" "blkuc12" "3840,895.19" "1" "1" "180")
(command "_insert" "blkuc12" "3840,895.93" "1" "1" "0")
(command "_insert" "blkuc12" "3840,895.56" "1" "1" "180")
(command "_insert" "blkuc12" "3840,896.3" "1" "1" "0")
(command "_insert" "blkuc12" "3840,895.93" "1" "1" "180")
(command "_insert" "blkuc12" "3840,896.67" "1" "1" "0")
(command "_insert" "blkuc12" "3840,896.3" "1" "1" "180")
(command "_insert" "blkuc12" "3840,897.04" "1" "1" "0")
(command "_insert" "blkuc12" "3840,896.67" "1" "1" "180")
(command "_insert" "blkuc12" "3840,897.41" "1" "1" "0")
(command "_insert" "blkuc12" "3840,897.04" "1" "1" "180")
(command "_insert" "blkuc12" "3840,897.78" "1" "1" "0")
(command "_insert" "blkuc12" "3840,897.41" "1" "1" "180")
(command "_insert" "blkuc12" "3840,898.15" "1" "1" "0")
(command "_insert" "blkuc12" "3840,897.78" "1" "1" "180")
(command "_insert" "blkuc12" "3840,898.52" "1" "1" "0")
(command "_insert" "blkuc12" "3840,898.15" "1" "1" "180")
(command "_insert" "blkuc12" "3840,898.89" "1" "1" "0")
(command "_insert" "blkuc12" "3840,898.52" "1" "1" "180")
(command "_insert" "blkuc12" "3840,899.26" "1" "1" "0")
(command "_insert" "blkuc12" "3840,898.89" "1" "1" "180")
(command "_insert" "blkuc12" "3840,899.63" "1" "1" "0")
(command "_insert" "blkuc12" "3840,899.26" "1" "1" "180")
(command "_insert" "blkuc12" "3840,900" "1" "1" "0")
(command "_insert" "blkuc12" "3840,899.63" "1" "1" "180")
(command "_insert" "blkuc12" "3840,900.37" "1" "1" "0")
(command "_insert" "blkuc12" "3840,900" "1" "1" "180")
(command "_insert" "blkuc12" "3840,900.74" "1" "1" "0")
(command "_insert" "blkuc12" "3840,900.37" "1" "1" "180")
(command "_insert" "blkuc12" "3840,901.11" "1" "1" "0")
(command "_insert" "blkuc12" "3840,900.74" "1" "1" "180")
(command "_insert" "blkuc12" "3840,901.48" "1" "1" "0")
(command "_insert" "blkuc12" "3840,901.11" "1" "1" "180")
(command "_insert" "blkuc12" "3840,901.85" "1" "1" "0")
(command "_insert" "blkuc12" "3840,901.48" "1" "1" "180")
(command "_insert" "blkuc12" "3840,902.22" "1" "1" "0")
(command "_insert" "blkuc12" "3840,901.85" "1" "1" "180")
(command "_insert" "blkuc12" "3840,902.59" "1" "1" "0")
(command "_insert" "blkuc12" "3840,902.22" "1" "1" "180")
(command "_insert" "blkuc12" "3840,902.96" "1" "1" "0")
(command "_insert" "blkuc12" "3840,902.59" "1" "1" "180")
(command "_insert" "blkuc12" "3840,903.33" "1" "1" "0")
(command "_insert" "blkuc12" "3840,902.96" "1" "1" "180")
(command "_insert" "blkuc12" "3840,903.7" "1" "1" "0")
(command "_insert" "blkuc12" "3840,903.33" "1" "1" "180")
(command "_insert" "blkuc12" "3840,904.07" "1" "1" "0")
(command "_insert" "blkuc12" "3840,903.7" "1" "1" "180")
(command "_insert" "blkuc12" "3840,904.44" "1" "1" "0")
(command "_insert" "blkuc12" "3840,904.07" "1" "1" "180")
(command "_insert" "blkuc12" "3840,904.81" "1" "1" "0")
(command "_insert" "blkuc12" "3840,904.44" "1" "1" "180")
(command "_insert" "blkuc12" "3840,905.18" "1" "1" "0")
(command "_insert" "blkuc12" "3840,904.81" "1" "1" "180")
(command "_insert" "blkuc12" "3840,905.55" "1" "1" "0")
(command "_insert" "blkuc12" "3840,905.18" "1" "1" "180")
(command "_insert" "blkuc12" "3840,905.92" "1" "1" "0")
(command "_insert" "blkuc12" "3840,905.55" "1" "1" "180")
(command "_insert" "blkuc12" "3840,906.29" "1" "1" "0")
(command "_insert" "blkuc12" "3840,905.92" "1" "1" "180")
(command "_insert" "blkuc12" "3840,906.66" "1" "1" "0")
(command "_insert" "blkuc12" "3840,906.29" "1" "1" "180")
(command "_insert" "blkuc12" "3840,907.03" "1" "1" "0")
(command "_insert" "blkuc12" "3840,906.66" "1" "1" "180")
(command "_insert" "blkuc12" "3840,907.4" "1" "1" "0")
(command "_insert" "blkuc12" "3840,907.03" "1" "1" "180")
(command "_insert" "blkuc12" "3840,907.77" "1" "1" "0")
(command "_insert" "blkuc12" "3840,907.4" "1" "1" "180")
(command "_insert" "blkuc12" "3840,908.14" "1" "1" "0")
(command "_insert" "blkuc12" "3840,907.77" "1" "1" "180")
(command "_insert" "blkuc12" "3840,908.51" "1" "1" "0")
(command "_insert" "blkuc12" "3840,908.14" "1" "1" "180")
(command "_insert" "blkuc12" "3840,908.88" "1" "1" "0")
(command "_insert" "blkuc12" "3840,908.51" "1" "1" "180")
(command "_insert" "blkuc12" "3840,909.25" "1" "1" "0")
(command "_insert" "blkuc12" "3840,908.88" "1" "1" "180")
(command "_insert" "blkuc12" "3840,909.62" "1" "1" "0")
(command "_insert" "blkuc12" "3840,909.25" "1" "1" "180")
(command "_insert" "blkuc12" "3840,909.99" "1" "1" "0")
(command "_insert" "blkuc12" "3840,909.62" "1" "1" "180")
(command "_insert" "blkuc12" "3840,910.36" "1" "1" "0")
(command "_insert" "blkuc12" "3840,909.99" "1" "1" "180")
(command "_insert" "blkuc12" "3840,910.73" "1" "1" "0")
(command "_insert" "blkuc12" "3840,910.36" "1" "1" "180")
(command "_insert" "blkuc12" "3840,911.1" "1" "1" "0")
(command "_insert" "blkuc12" "3840,910.73" "1" "1" "180")
(command "_insert" "blkuc12" "3840,911.47" "1" "1" "0")
(command "_insert" "blkuc12" "3840,911.1" "1" "1" "180")
(command "_insert" "blkuc12" "3840,911.84" "1" "1" "0")
(command "_insert" "blkuc12" "3840,911.47" "1" "1" "180")
(command "_insert" "blkuc12" "3840,912.21" "1" "1" "0")
(command "_insert" "blkuc12" "3840,911.84" "1" "1" "180")
(command "_insert" "blkuc12" "3840,912.58" "1" "1" "0")
(command "_insert" "blkuc12" "3840,912.21" "1" "1" "180")
(command "_insert" "blkuc12" "3840,912.95" "1" "1" "0")
(command "_insert" "blkuc12" "3840,912.58" "1" "1" "180")
(command "_insert" "blkuc12" "3840,913.32" "1" "1" "0")
(command "_insert" "blkuc12" "3840,912.95" "1" "1" "180")
(command "_insert" "blkuc12" "3840,913.69" "1" "1" "0")
(command "_insert" "blkuc12" "3840,913.32" "1" "1" "180")
(command "_insert" "blkuc12" "3840,914.06" "1" "1" "0")
(command "_insert" "blkuc12" "3840,913.69" "1" "1" "180")
(command "_insert" "blkuc12" "3840,914.43" "1" "1" "0")
(command "_insert" "blkuc12" "3840,914.06" "1" "1" "180")
(command "_insert" "blkuc12" "3840,914.8" "1" "1" "0")
(command "_insert" "blkuc12" "3840,914.43" "1" "1" "180")
(command "_insert" "blkuc12" "3840,915.17" "1" "1" "0")
(command "_insert" "blkuc12" "3840,914.8" "1" "1" "180")
(command "_insert" "blkuc12" "3840,915.54" "1" "1" "0")
(command "_insert" "blkuc12" "3840,915.17" "1" "1" "180")
(command "_insert" "blkuc12" "3840,915.91" "1" "1" "0")
(command "_insert" "blkuc12" "3840,915.54" "1" "1" "180")
(command "_insert" "blkuc12" "3840,916.28" "1" "1" "0")
(command "_insert" "blkuc12" "3840,915.91" "1" "1" "180")
(command "_insert" "blkuc12" "3840,916.65" "1" "1" "0")
(command "_insert" "blkuc12" "3840,916.28" "1" "1" "180")
(command "_insert" "blkuc12" "3840,917.02" "1" "1" "0")
(command "_insert" "blkuc12" "3840,916.65" "1" "1" "180")
(command "_insert" "blkuc12" "3840,917.39" "1" "1" "0")
(command "_insert" "blkuc12" "3840,917.02" "1" "1" "180")
(command "_insert" "blkuc12" "3840,917.76" "1" "1" "0")
(command "_insert" "blkuc12" "3840,917.39" "1" "1" "180")
(command "_insert" "blkuc12" "3840,918.13" "1" "1" "0")
(command "_insert" "blkuc12" "3840,917.76" "1" "1" "180")
(command "_insert" "blkuc12" "3840,918.5" "1" "1" "0")
(command "_insert" "blkuc12" "3840,918.13" "1" "1" "180")
(command "_insert" "blkuc12" "3840,918.87" "1" "1" "0")
(command "_insert" "blkuc12" "3840,918.5" "1" "1" "180")
(command "_insert" "blkuc12" "3840,919.24" "1" "1" "0")
(command "_insert" "blkuc12" "3840,918.87" "1" "1" "180")
(command "_insert" "blkuc12" "3840,919.61" "1" "1" "0")
(command "_insert" "blkuc12" "3840,919.24" "1" "1" "180")
(command "_insert" "blkuc12" "3840,919.98" "1" "1" "0")
(command "_insert" "blkuc12" "3840,919.61" "1" "1" "180")
(command "_insert" "blkuc12" "3840,920.35" "1" "1" "0")
(command "_insert" "blkuc12" "3840,919.98" "1" "1" "180")
(command "_insert" "blkuc12" "3840,920.72" "1" "1" "0")
(command "_insert" "blkuc12" "3840,920.35" "1" "1" "180")
(command "_insert" "blkuc12" "3840,921.09" "1" "1" "0")
(command "_insert" "blkuc12" "3840,920.72" "1" "1" "180")
(command "_insert" "blkuc12" "3840,921.46" "1" "1" "0")
(command "_insert" "blkuc12" "3840,921.09" "1" "1" "180")
(command "_insert" "blkuc12" "3840,921.83" "1" "1" "0")
(command "_insert" "blkuc12" "3840,921.46" "1" "1" "180")
(command "_insert" "blkuc12" "3840,922.2" "1" "1" "0")
(command "_insert" "blkuc12" "3840,921.83" "1" "1" "180")
(command "_insert" "blkuc12" "3840,922.57" "1" "1" "0")
(command "_insert" "blkuc12" "3840,922.2" "1" "1" "180")
(command "_insert" "blkuc12" "3840,922.94" "1" "1" "0")
(command "_insert" "blkuc12" "3840,922.57" "1" "1" "180")
(command "_insert" "blkuc12" "3840,923.31" "1" "1" "0")
(command "_insert" "blkuc12" "3840,922.94" "1" "1" "180")
(command "_insert" "blkuc12" "3840,923.68" "1" "1" "0")
(command "_insert" "blkuc12" "3840,923.31" "1" "1" "180")
(command "_insert" "blkuc12" "3840,924.05" "1" "1" "0")
(command "_insert" "blkuc12" "3840,923.68" "1" "1" "180")
(command "_insert" "blkuc12" "3840,924.42" "1" "1" "0")
(command "_insert" "blkuc12" "3840,924.05" "1" "1" "180")
(command "_insert" "blkuc12" "3840,924.79" "1" "1" "0")
(command "_insert" "blkuc12" "3840,924.42" "1" "1" "180")
(command "_insert" "blkuc12" "3840,925.16" "1" "1" "0")
(command "_insert" "blkuc12" "3840,924.79" "1" "1" "180")
(command "_insert" "blkuc12" "3840,925.53" "1" "1" "0")
(command "_insert" "blkuc12" "3840,925.16" "1" "1" "180")
(command "_insert" "blkuc12" "3840,925.9" "1" "1" "0")
(command "_insert" "blkuc12" "3840,925.53" "1" "1" "180")
(command "_insert" "blkuc12" "3840,926.27" "1" "1" "0")
(command "_insert" "blkuc12" "3840,925.9" "1" "1" "180")
(command "_insert" "blkuc12" "3840,926.64" "1" "1" "0")
(command "_insert" "blkuc12" "3840,926.27" "1" "1" "180")
(command "_insert" "blkuc12" "3840,927.01" "1" "1" "0")
(command "_insert" "blkuc12" "3840,926.64" "1" "1" "180")
(command "_insert" "blkuc12" "3840,927.38" "1" "1" "0")
(command "_insert" "blkuc12" "3840,927.01" "1" "1" "180")
(command "_insert" "blkuc12" "3840,927.75" "1" "1" "0")
(command "_insert" "blkuc12" "3840,927.38" "1" "1" "180")
(command "_layer" "set" "phccover" "")
(command "_rectangle" "3838.884,933.3" "3841.116,866.7")
(command "_layer" "set" "nitride" "")
(setq phc12 currobj)
(command "_layer" "set" "cover" "")
(command "_rectangle" "3838.884,836.7" "3841.116,963.3")
(command "_layer" "set" "nitride" "")
(command "_layer" "set" "text" "")
(command "_circle" "3837.934,846.7" "0.075")
(command "_circle" "3837.559,846.7" "0.15")
(command "_circle" "3837.184,846.7" "0.075")
(command "_circle" "3836.809,846.7" "0.15")
(command "_circle" "3837.934,848.7" "0.075")
(command "_circle" "3837.559,848.7" "0.075")
(command "_circle" "3837.184,848.7" "0.15")
(command "_circle" "3836.809,848.7" "0.15")
(command "_circle" "3837.934,850.7" "0.075")
(command "_circle" "3837.559,850.7" "0.15")
(command "_circle" "3837.184,850.7" "0.15")
(command "_circle" "3836.809,850.7" "0.15")
(command "_circle" "3837.934,852.7" "0.075")
(command "_circle" "3837.559,852.7" "0.075")
(command "_circle" "3837.184,852.7" "0.075")
(command "_circle" "3836.809,852.7" "0.075")
(command "_circle" "3836.434,852.7" "0.15")
(command "_circle" "3837.934,854.7" "0.075")
(command "_circle" "3837.559,854.7" "0.15")
(command "_circle" "3837.184,854.7" "0.075")
(command "_circle" "3836.809,854.7" "0.075")
(command "_circle" "3836.434,854.7" "0.15")
(command "_circle" "3837.934,856.7" "0.075")
(command "_circle" "3837.559,856.7" "0.075")
(command "_circle" "3837.184,856.7" "0.15")
(command "_circle" "3836.809,856.7" "0.075")
(command "_circle" "3836.434,856.7" "0.15")
(command "_circle" "3837.934,858.7" "0.075")
(command "_circle" "3837.559,858.7" "0.15")
(command "_circle" "3837.184,858.7" "0.15")
(command "_circle" "3836.809,858.7" "0.075")
(command "_circle" "3836.434,858.7" "0.15")
(command "_circle" "3837.934,860.7" "0.075")
(command "_circle" "3837.559,860.7" "0.075")
(command "_circle" "3837.184,860.7" "0.075")
(command "_circle" "3836.809,860.7" "0.15")
(command "_circle" "3836.434,860.7" "0.15")
(command "_circle" "3837.934,862.7" "0.075")
(command "_circle" "3837.559,862.7" "0.15")
(command "_circle" "3837.184,862.7" "0.075")
(command "_circle" "3836.809,862.7" "0.15")
(command "_circle" "3836.434,862.7" "0.15")
(command "_circle" "3837.934,864.7" "0.075")
(command "_circle" "3837.559,864.7" "0.075")
(command "_circle" "3837.184,864.7" "0.15")
(command "_circle" "3836.809,864.7" "0.15")
(command "_circle" "3836.434,864.7" "0.15")
(command "_circle" "3837.934,866.7" "0.075")
(command "_circle" "3837.559,866.7" "0.15")
(command "_circle" "3837.184,866.7" "0.15")
(command "_circle" "3836.809,866.7" "0.15")
(command "_circle" "3836.434,866.7" "0.15")
(command "_circle" "3837.934,868.7" "0.075")
(command "_circle" "3837.559,868.7" "0.075")
(command "_circle" "3837.184,868.7" "0.075")
(command "_circle" "3836.809,868.7" "0.075")
(command "_circle" "3836.434,868.7" "0.075")
(command "_circle" "3836.059,868.7" "0.15")
(command "_circle" "3837.934,870.7" "0.075")
(command "_circle" "3837.559,870.7" "0.15")
(command "_circle" "3837.184,870.7" "0.075")
(command "_circle" "3836.809,870.7" "0.075")
(command "_circle" "3836.434,870.7" "0.075")
(command "_circle" "3836.059,870.7" "0.15")
(command "_circle" "3837.934,872.7" "0.075")
(command "_circle" "3837.559,872.7" "0.075")
(command "_circle" "3837.184,872.7" "0.15")
(command "_circle" "3836.809,872.7" "0.075")
(command "_circle" "3836.434,872.7" "0.075")
(command "_circle" "3836.059,872.7" "0.15")
(command "_circle" "3837.934,874.7" "0.075")
(command "_circle" "3837.559,874.7" "0.15")
(command "_circle" "3837.184,874.7" "0.15")
(command "_circle" "3836.809,874.7" "0.075")
(command "_circle" "3836.434,874.7" "0.075")
(command "_circle" "3836.059,874.7" "0.15")
(command "_circle" "3837.934,876.7" "0.075")
(command "_circle" "3837.559,876.7" "0.075")
(command "_circle" "3837.184,876.7" "0.075")
(command "_circle" "3836.809,876.7" "0.15")
(command "_circle" "3836.434,876.7" "0.075")
(command "_circle" "3836.059,876.7" "0.15")
(command "_circle" "3837.934,878.7" "0.075")
(command "_circle" "3837.559,878.7" "0.15")
(command "_circle" "3837.184,878.7" "0.075")
(command "_circle" "3836.809,878.7" "0.15")
(command "_circle" "3836.434,878.7" "0.075")
(command "_circle" "3836.059,878.7" "0.15")
(command "_circle" "3837.934,880.7" "0.075")
(command "_circle" "3837.559,880.7" "0.075")
(command "_circle" "3837.184,880.7" "0.15")
(command "_circle" "3836.809,880.7" "0.15")
(command "_circle" "3836.434,880.7" "0.075")
(command "_circle" "3836.059,880.7" "0.15")
(command "_circle" "3837.934,882.7" "0.075")
(command "_circle" "3837.559,882.7" "0.15")
(command "_circle" "3837.184,882.7" "0.15")
(command "_circle" "3836.809,882.7" "0.15")
(command "_circle" "3836.434,882.7" "0.075")
(command "_circle" "3836.059,882.7" "0.15")
(command "_circle" "3837.934,884.7" "0.075")
(command "_circle" "3837.559,884.7" "0.075")
(command "_circle" "3837.184,884.7" "0.075")
(command "_circle" "3836.809,884.7" "0.075")
(command "_circle" "3836.434,884.7" "0.15")
(command "_circle" "3836.059,884.7" "0.15")
(command "_circle" "3837.934,886.7" "0.075")
(command "_circle" "3837.559,886.7" "0.15")
(command "_circle" "3837.184,886.7" "0.075")
(command "_circle" "3836.809,886.7" "0.075")
(command "_circle" "3836.434,886.7" "0.15")
(command "_circle" "3836.059,886.7" "0.15")
(command "_circle" "3837.934,888.7" "0.075")
(command "_circle" "3837.559,888.7" "0.075")
(command "_circle" "3837.184,888.7" "0.15")
(command "_circle" "3836.809,888.7" "0.075")
(command "_circle" "3836.434,888.7" "0.15")
(command "_circle" "3836.059,888.7" "0.15")
(command "_circle" "3837.934,890.7" "0.075")
(command "_circle" "3837.559,890.7" "0.15")
(command "_circle" "3837.184,890.7" "0.15")
(command "_circle" "3836.809,890.7" "0.075")
(command "_circle" "3836.434,890.7" "0.15")
(command "_circle" "3836.059,890.7" "0.15")
(command "_circle" "3837.934,892.7" "0.075")
(command "_circle" "3837.559,892.7" "0.075")
(command "_circle" "3837.184,892.7" "0.075")
(command "_circle" "3836.809,892.7" "0.15")
(command "_circle" "3836.434,892.7" "0.15")
(command "_circle" "3836.059,892.7" "0.15")
(command "_circle" "3837.934,894.7" "0.075")
(command "_circle" "3837.559,894.7" "0.15")
(command "_circle" "3837.184,894.7" "0.075")
(command "_circle" "3836.809,894.7" "0.15")
(command "_circle" "3836.434,894.7" "0.15")
(command "_circle" "3836.059,894.7" "0.15")
(command "_circle" "3837.934,896.7" "0.075")
(command "_circle" "3837.559,896.7" "0.075")
(command "_circle" "3837.184,896.7" "0.15")
(command "_circle" "3836.809,896.7" "0.15")
(command "_circle" "3836.434,896.7" "0.15")
(command "_circle" "3836.059,896.7" "0.15")
(command "_circle" "3837.934,898.7" "0.075")
(command "_circle" "3837.559,898.7" "0.15")
(command "_circle" "3837.184,898.7" "0.15")
(command "_circle" "3836.809,898.7" "0.15")
(command "_circle" "3836.434,898.7" "0.15")
(command "_circle" "3836.059,898.7" "0.15")
(command "_circle" "3837.934,900.7" "0.075")
(command "_circle" "3837.559,900.7" "0.075")
(command "_circle" "3837.184,900.7" "0.075")
(command "_circle" "3836.809,900.7" "0.075")
(command "_circle" "3836.434,900.7" "0.075")
(command "_circle" "3836.059,900.7" "0.075")
(command "_circle" "3835.684,900.7" "0.15")
(command "_circle" "3837.934,902.7" "0.075")
(command "_circle" "3837.559,902.7" "0.15")
(command "_circle" "3837.184,902.7" "0.075")
(command "_circle" "3836.809,902.7" "0.075")
(command "_circle" "3836.434,902.7" "0.075")
(command "_circle" "3836.059,902.7" "0.075")
(command "_circle" "3835.684,902.7" "0.15")
(command "_circle" "3837.934,904.7" "0.075")
(command "_circle" "3837.559,904.7" "0.075")
(command "_circle" "3837.184,904.7" "0.15")
(command "_circle" "3836.809,904.7" "0.075")
(command "_circle" "3836.434,904.7" "0.075")
(command "_circle" "3836.059,904.7" "0.075")
(command "_circle" "3835.684,904.7" "0.15")
(command "_circle" "3837.934,906.7" "0.075")
(command "_circle" "3837.559,906.7" "0.15")
(command "_circle" "3837.184,906.7" "0.15")
(command "_circle" "3836.809,906.7" "0.075")
(command "_circle" "3836.434,906.7" "0.075")
(command "_circle" "3836.059,906.7" "0.075")
(command "_circle" "3835.684,906.7" "0.15")
(command "_circle" "3837.934,908.7" "0.075")
(command "_circle" "3837.559,908.7" "0.075")
(command "_circle" "3837.184,908.7" "0.075")
(command "_circle" "3836.809,908.7" "0.15")
(command "_circle" "3836.434,908.7" "0.075")
(command "_circle" "3836.059,908.7" "0.075")
(command "_circle" "3835.684,908.7" "0.15")
(command "_circle" "3837.934,910.7" "0.075")
(command "_circle" "3837.559,910.7" "0.15")
(command "_circle" "3837.184,910.7" "0.075")
(command "_circle" "3836.809,910.7" "0.15")
(command "_circle" "3836.434,910.7" "0.075")
(command "_circle" "3836.059,910.7" "0.075")
(command "_circle" "3835.684,910.7" "0.15")
(command "_circle" "3837.934,912.7" "0.075")
(command "_circle" "3837.559,912.7" "0.075")
(command "_circle" "3837.184,912.7" "0.15")
(command "_circle" "3836.809,912.7" "0.15")
(command "_circle" "3836.434,912.7" "0.075")
(command "_circle" "3836.059,912.7" "0.075")
(command "_circle" "3835.684,912.7" "0.15")
(command "_circle" "3837.934,914.7" "0.075")
(command "_circle" "3837.559,914.7" "0.15")
(command "_circle" "3837.184,914.7" "0.15")
(command "_circle" "3836.809,914.7" "0.15")
(command "_circle" "3836.434,914.7" "0.075")
(command "_circle" "3836.059,914.7" "0.075")
(command "_circle" "3835.684,914.7" "0.15")
(command "_circle" "3837.934,916.7" "0.075")
(command "_circle" "3837.559,916.7" "0.075")
(command "_circle" "3837.184,916.7" "0.075")
(command "_circle" "3836.809,916.7" "0.075")
(command "_circle" "3836.434,916.7" "0.15")
(command "_circle" "3836.059,916.7" "0.075")
(command "_circle" "3835.684,916.7" "0.15")
(command "_circle" "3837.934,918.7" "0.075")
(command "_circle" "3837.559,918.7" "0.15")
(command "_circle" "3837.184,918.7" "0.075")
(command "_circle" "3836.809,918.7" "0.075")
(command "_circle" "3836.434,918.7" "0.15")
(command "_circle" "3836.059,918.7" "0.075")
(command "_circle" "3835.684,918.7" "0.15")
(command "_circle" "3837.934,920.7" "0.075")
(command "_circle" "3837.559,920.7" "0.075")
(command "_circle" "3837.184,920.7" "0.15")
(command "_circle" "3836.809,920.7" "0.075")
(command "_circle" "3836.434,920.7" "0.15")
(command "_circle" "3836.059,920.7" "0.075")
(command "_circle" "3835.684,920.7" "0.15")
(command "_circle" "3837.934,922.7" "0.075")
(command "_circle" "3837.559,922.7" "0.15")
(command "_circle" "3837.184,922.7" "0.15")
(command "_circle" "3836.809,922.7" "0.075")
(command "_circle" "3836.434,922.7" "0.15")
(command "_circle" "3836.059,922.7" "0.075")
(command "_circle" "3835.684,922.7" "0.15")
(command "_circle" "3837.934,924.7" "0.075")
(command "_circle" "3837.559,924.7" "0.075")
(command "_circle" "3837.184,924.7" "0.075")
(command "_circle" "3836.809,924.7" "0.15")
(command "_circle" "3836.434,924.7" "0.15")
(command "_circle" "3836.059,924.7" "0.075")
(command "_circle" "3835.684,924.7" "0.15")
(command "_circle" "3837.934,926.7" "0.075")
(command "_circle" "3837.559,926.7" "0.15")
(command "_circle" "3837.184,926.7" "0.075")
(command "_circle" "3836.809,926.7" "0.15")
(command "_circle" "3836.434,926.7" "0.15")
(command "_circle" "3836.059,926.7" "0.075")
(command "_circle" "3835.684,926.7" "0.15")
(command "_circle" "3837.934,928.7" "0.075")
(command "_circle" "3837.559,928.7" "0.075")
(command "_circle" "3837.184,928.7" "0.15")
(command "_circle" "3836.809,928.7" "0.15")
(command "_circle" "3836.434,928.7" "0.15")
(command "_circle" "3836.059,928.7" "0.075")
(command "_circle" "3835.684,928.7" "0.15")
(command "_circle" "3837.934,930.7" "0.075")
(command "_circle" "3837.559,930.7" "0.15")
(command "_circle" "3837.184,930.7" "0.15")
(command "_circle" "3836.809,930.7" "0.15")
(command "_circle" "3836.434,930.7" "0.15")
(command "_circle" "3836.059,930.7" "0.075")
(command "_circle" "3835.684,930.7" "0.15")
(command "_circle" "3837.934,932.7" "0.075")
(command "_circle" "3837.559,932.7" "0.075")
(command "_circle" "3837.184,932.7" "0.075")
(command "_circle" "3836.809,932.7" "0.075")
(command "_circle" "3836.434,932.7" "0.075")
(command "_circle" "3836.059,932.7" "0.15")
(command "_circle" "3835.684,932.7" "0.15")
(command "_circle" "3837.934,934.7" "0.075")
(command "_circle" "3837.559,934.7" "0.15")
(command "_circle" "3837.184,934.7" "0.075")
(command "_circle" "3836.809,934.7" "0.075")
(command "_circle" "3836.434,934.7" "0.075")
(command "_circle" "3836.059,934.7" "0.15")
(command "_circle" "3835.684,934.7" "0.15")
(command "_circle" "3837.934,936.7" "0.075")
(command "_circle" "3837.559,936.7" "0.075")
(command "_circle" "3837.184,936.7" "0.15")
(command "_circle" "3836.809,936.7" "0.075")
(command "_circle" "3836.434,936.7" "0.075")
(command "_circle" "3836.059,936.7" "0.15")
(command "_circle" "3835.684,936.7" "0.15")
(command "_circle" "3837.934,938.7" "0.075")
(command "_circle" "3837.559,938.7" "0.15")
(command "_circle" "3837.184,938.7" "0.15")
(command "_circle" "3836.809,938.7" "0.075")
(command "_circle" "3836.434,938.7" "0.075")
(command "_circle" "3836.059,938.7" "0.15")
(command "_circle" "3835.684,938.7" "0.15")
(command "_circle" "3837.934,940.7" "0.075")
(command "_circle" "3837.559,940.7" "0.075")
(command "_circle" "3837.184,940.7" "0.075")
(command "_circle" "3836.809,940.7" "0.15")
(command "_circle" "3836.434,940.7" "0.075")
(command "_circle" "3836.059,940.7" "0.15")
(command "_circle" "3835.684,940.7" "0.15")
(command "_circle" "3837.934,942.7" "0.075")
(command "_circle" "3837.559,942.7" "0.15")
(command "_circle" "3837.184,942.7" "0.075")
(command "_circle" "3836.809,942.7" "0.15")
(command "_circle" "3836.434,942.7" "0.075")
(command "_circle" "3836.059,942.7" "0.15")
(command "_circle" "3835.684,942.7" "0.15")
(command "_circle" "3837.934,944.7" "0.075")
(command "_circle" "3837.559,944.7" "0.075")
(command "_circle" "3837.184,944.7" "0.15")
(command "_circle" "3836.809,944.7" "0.15")
(command "_circle" "3836.434,944.7" "0.075")
(command "_circle" "3836.059,944.7" "0.15")
(command "_circle" "3835.684,944.7" "0.15")
(command "_circle" "3837.934,946.7" "0.075")
(command "_circle" "3837.559,946.7" "0.15")
(command "_circle" "3837.184,946.7" "0.15")
(command "_circle" "3836.809,946.7" "0.15")
(command "_circle" "3836.434,946.7" "0.075")
(command "_circle" "3836.059,946.7" "0.15")
(command "_circle" "3835.684,946.7" "0.15")
(command "_circle" "3837.934,948.7" "0.075")
(command "_circle" "3837.559,948.7" "0.075")
(command "_circle" "3837.184,948.7" "0.075")
(command "_circle" "3836.809,948.7" "0.075")
(command "_circle" "3836.434,948.7" "0.15")
(command "_circle" "3836.059,948.7" "0.15")
(command "_circle" "3835.684,948.7" "0.15")
(command "_circle" "3837.934,950.7" "0.075")
(command "_circle" "3837.559,950.7" "0.15")
(command "_circle" "3837.184,950.7" "0.075")
(command "_circle" "3836.809,950.7" "0.075")
(command "_circle" "3836.434,950.7" "0.15")
(command "_circle" "3836.059,950.7" "0.15")
(command "_circle" "3835.684,950.7" "0.15")
(command "_circle" "3837.934,952.7" "0.075")
(command "_circle" "3837.559,952.7" "0.075")
(command "_circle" "3837.184,952.7" "0.15")
(command "_circle" "3836.809,952.7" "0.075")
(command "_circle" "3836.434,952.7" "0.15")
(command "_circle" "3836.059,952.7" "0.15")
(command "_circle" "3835.684,952.7" "0.15")
(command "_circle" "3837.934,954.7" "0.075")
(command "_circle" "3837.559,954.7" "0.15")
(command "_circle" "3837.184,954.7" "0.15")
(command "_circle" "3836.809,954.7" "0.075")
(command "_circle" "3836.434,954.7" "0.15")
(command "_circle" "3836.059,954.7" "0.15")
(command "_circle" "3835.684,954.7" "0.15")
(command "_circle" "3837.934,956.7" "0.075")
(command "_circle" "3837.559,956.7" "0.075")
(command "_circle" "3837.184,956.7" "0.075")
(command "_circle" "3836.809,956.7" "0.15")
(command "_circle" "3836.434,956.7" "0.15")
(command "_circle" "3836.059,956.7" "0.15")
(command "_circle" "3835.684,956.7" "0.15")
(command "_circle" "3837.934,958.7" "0.075")
(command "_circle" "3837.559,958.7" "0.15")
(command "_circle" "3837.184,958.7" "0.075")
(command "_circle" "3836.809,958.7" "0.15")
(command "_circle" "3836.434,958.7" "0.15")
(command "_circle" "3836.059,958.7" "0.15")
(command "_circle" "3835.684,958.7" "0.15")
(command "_circle" "3837.934,960.7" "0.075")
(command "_circle" "3837.559,960.7" "0.075")
(command "_circle" "3837.184,960.7" "0.15")
(command "_circle" "3836.809,960.7" "0.15")
(command "_circle" "3836.434,960.7" "0.15")
(command "_circle" "3836.059,960.7" "0.15")
(command "_circle" "3835.684,960.7" "0.15")
(command "_circle" "3837.934,962.7" "0.075")
(command "_circle" "3837.559,962.7" "0.15")
(command "_circle" "3837.184,962.7" "0.15")
(command "_circle" "3836.809,962.7" "0.15")
(command "_circle" "3836.434,962.7" "0.15")
(command "_circle" "3836.059,962.7" "0.15")
(command "_circle" "3835.684,962.7" "0.15")
(command "_layer" "set" "nitride" "")
(command "_layer" "set" "text" "")
(command-s "_text" "3826.884,963.3" "2" "-90" "a = 370 nm" )
(sssetfirst nil (ssget "_L"))
(if (not (numberp (vl-string-search "Mac" (getvar "platform")))) (c:txtexp))
(command "_layer" "set" "nitride" "")
(command "_layer" "set" "text" "")
(command-s "_text" "3823.884,963.3" "2" "-90" "gap = 270 nm" )
(sssetfirst nil (ssget "_L"))
(if (not (numberp (vl-string-search "Mac" (getvar "platform")))) (c:txtexp))
(command "_layer" "set" "nitride" "")
(command "_layer" "set" "text" "")
(command-s "_text" "3820.884,963.3" "2" "-90" "amplitude = 137 nm" )
(sssetfirst nil (ssget "_L"))
(if (not (numberp (vl-string-search "Mac" (getvar "platform")))) (c:txtexp))
(command "_layer" "set" "nitride" "")
(command "_layer" "set" "text" "")
(command-s "_text" "3817.884,963.3" "2" "-90" "start width = 280 nm" )
(sssetfirst nil (ssget "_L"))
(if (not (numberp (vl-string-search "Mac" (getvar "platform")))) (c:txtexp))
(command "_layer" "set" "nitride" "")
(command "_layer" "set" "text" "")
(command-s "_text" "3814.884,963.3" "2" "-90" "width = 286 nm" )
(sssetfirst nil (ssget "_L"))
(if (not (numberp (vl-string-search "Mac" (getvar "platform")))) (c:txtexp))
(command "_layer" "set" "nitride" "")
(command "_layer" "set" "text" "")
(command-s "_text" "3811.884,963.3" "2" "-90" "taper: 15" )
(sssetfirst nil (ssget "_L"))
(if (not (numberp (vl-string-search "Mac" (getvar "platform")))) (c:txtexp))
(command "_layer" "set" "nitride" "")
(command "_layer" "set" "text" "")
(command-s "_text" "3808.884,963.3" "2" "-90" "nominal: 150" )
(sssetfirst nil (ssget "_L"))
(if (not (numberp (vl-string-search "Mac" (getvar "platform")))) (c:txtexp))
(command "_layer" "set" "nitride" "")
(command "_layer" "set" "indicators" "")
(setq coords (list 
(list 3760.415 940) 
(list 3760.415 920) 
(list 3740.415 900) 
(list 3760.415 880) 
(list 3760.415 860) 
(list 3760.415 900) 
(list 3760.415 887.0711) 
(list 3747.4861 900) 
(list 3760.415 912.9289) 
(list 3760.415 900)))
(apply 'command (append '("pline") coords '("c")))
(command "._fillet" "radius" "1" "._fillet" "P" (entlast))
(setq coords (list 
(list 3919.585 940) 
(list 3919.585 920) 
(list 3939.585 900) 
(list 3919.585 880) 
(list 3919.585 860) 
(list 3919.585 900) 
(list 3919.585 887.0711) 
(list 3932.5139 900) 
(list 3919.585 912.9289) 
(list 3919.585 900)))
(apply 'command (append '("pline") coords '("c")))
(command "._fillet" "radius" "1" "._fillet" "P" (entlast))
(command "_layer" "set" "holes" "")
(command "_circle" "3758.0629,914.1124" "0.5")
(command "_circle" "3755.7109,911.7603" "0.5")
(command "_circle" "3753.3588,909.4083" "0.5")
(command "_circle" "3751.0067,907.0562" "0.5")
(command "_circle" "3748.6547,904.7041" "0.5")
(command "_circle" "3746.3026,902.3521" "0.5")
(command "_circle" "3743.9505,900" "0.5")
(command "_circle" "3746.3026,897.6479" "0.5")
(command "_circle" "3748.6547,895.2959" "0.5")
(command "_circle" "3751.0067,892.9438" "0.5")
(command "_circle" "3753.3588,890.5917" "0.5")
(command "_circle" "3755.7109,888.2397" "0.5")
(command "_circle" "3758.0629,885.8876" "0.5")
(command "_circle" "3921.9371,914.1124" "0.5")
(command "_circle" "3924.2891,911.7603" "0.5")
(command "_circle" "3926.6412,909.4083" "0.5")
(command "_circle" "3928.9933,907.0562" "0.5")
(command "_circle" "3931.3453,904.7041" "0.5")
(command "_circle" "3933.6974,902.3521" "0.5")
(command "_circle" "3936.0495,900" "0.5")
(command "_circle" "3933.6974,897.6479" "0.5")
(command "_circle" "3931.3453,895.2959" "0.5")
(command "_circle" "3928.9933,892.9438" "0.5")
(command "_circle" "3926.6412,890.5917" "0.5")
(command "_circle" "3924.2891,888.2397" "0.5")
(command "_circle" "3921.9371,885.8876" "0.5")
(command "_layer" "set" "nitride" "")
(command "_block" "blkcoupler12" "3840,900" coupler12 "")
(command "_insert" "blkcoupler12" "3840,900" "1" "1" "0")
(command "_insert" "blkcoupler12" "3840,900" "1" "1" "180")
(command "_block" "blksinglenanobeam12" "3840,900" singlenanobeam12 "")
(command "_insert" "blksinglenanobeam12" "3840,900" "1" "1" "0")
(command "_insert" "blksinglenanobeam12" "3840,900" "1" "1" "180")
(command "_block" "blkanglednodearray12" "3840,900" anglednodearray12 "")
(command "_insert" "blkanglednodearray12" "3840,900" "1" "1" "0")
(command "_insert" "blkanglednodearray12" "3840,900" "1" "1" "180")
(command "_block" "blkcooledsinglenanobeam12" "3840,900" cooledsinglenanobeam12 "")
(command "_insert" "blkcooledsinglenanobeam12" "3840,900" "1" "1" "0")
(command "_insert" "blkcooledsinglenanobeam12" "3840,900" "1" "1" "180")
(command "_block" "blkyjunction12" "3840,900" yjunction12 "")
(command "_insert" "blkyjunction12" "3840,900" "1" "1" "0")
(command "_insert" "blkyjunction12" "3840,900" "1" "1" "180")
; DRAWING BULGING VEE GROOVE
(command "_layer" "set" "vgroove" "")
(setq coords (list 
(list 3765.415 -605) 
(list 3765.415 0) 
(list 3765.415 0) 
(list 3765.415 1800) 
(list 3765.415 1800) 
(list 3765.415 2405) 
(list 3914.585 2405) 
(list 3914.585 1800) 
(list 3914.585 1800) 
(list 3914.585 0) 
(list 3914.585 0) 
(list 3914.585 -605)))
(apply 'command (append '("pline") coords '("c")))
(command "._fillet" "radius" "0" "._fillet" "P" (entlast))
(command "_layer" "set" "window" "")
(command "_rectangle" "3765.415,-1935" "3914.585,-600")
(command "_rectangle" "3765.415,2400" "3914.585,5300")
(command "_layer" "set" "grid" "")
(command "_rectangle" "3766.415,-1934" "3789.9433,-1909.2133")
(command "_array" "last" "" "R" "75" "3" "25.7867" "24.5283")
(command "_rectangle" "3841,-1934" "3864.5283,-1909.2133")
(command "_array" "last" "" "R" "75" "3" "25.7867" "24.5283")
(command "_rectangle" "3766.415,1" "3789.9433,25.7")
(command "_array" "last" "" "R" "70" "3" "25.7" "24.5283")
(command "_rectangle" "3841,1" "3864.5283,25.7")
(command "_array" "last" "" "R" "70" "3" "25.7" "24.5283")
(command "_rectangle" "3766.415,1801" "3789.9433,1825.9185")
(command "_array" "last" "" "R" "135" "3" "25.9185" "24.5283")
(command "_rectangle" "3841,1801" "3864.5283,1825.9185")
(command "_array" "last" "" "R" "135" "3" "25.9185" "24.5283")
(command "_layer" "set" "vgrooveFDA" "")
(command "_rectangle" "3914.585,-2233" "3765.415,-1933")
(command "_layer" "set" "nitride" "")
(command "_layer" "set" "holes" "")
(command "_circle" "3917.085,331.5" "0.5")
(command "_array" "last" "" "R" "379" "1" "3" "2.5")
(command "_circle" "3762.915,331.5" "0.5")
(command "_array" "last" "" "R" "379" "1" "3" "-2.5")
(command "_layer" "set" "nitride" "")
(command "_layer" "set" "window" "")
(command "_layer" "set" "window" "")
(command "_rectangle" "3919.585,0" "4080.415,1800")
(command "._fillet" "radius" "20" "._fillet" "P" (entlast))
(command "_layer" "set" "grid" "")
(command "_rectangle" "3920.585,1" "3942.4179,25.7")
(command "_array" "last" "" "R" "70" "7" "25.7" "22.8329")
(command "_layer" "set" "nitride" "")
; DRAWING REGION LAYER
(command "_layer" "set" "regionLayer12" "")
(command "_rectangle" "3760,-460" "3920,2260")
(command "_layer" "set" "nitride" "")
(setq coupler12 nil)
(setq singlenanobeam12 nil)
(setq anglednodearray12 nil)
(setq cooledsinglenanobeam12 nil)
(setq yjunction12 nil)
; DEVICE #13
(command "_layer" "set" "window" "")
(command "_circle" "4072.915,-415" "5")
(command "_circle" "4072.915,-402.5" "5")
(command "_circle" "4072.915,-390" "5")
(command "_circle" "4072.915,-377.5" "5")
(command "_circle" "4060.415,-415" "5")
(command "_circle" "4060.415,-402.5" "5")
(command "_circle" "4060.415,-390" "5")
(command "_circle" "4060.415,-377.5" "5")
(command "_circle" "4047.915,-415" "5")
(command "_circle" "4047.915,-402.5" "5")
(command "_circle" "4047.915,-390" "5")
(command "_circle" "4047.915,-377.5" "5")
(command "_circle" "4035.415,-415" "5")
(command "_layer" "set" "nitride" "")
(setq currobj nil)
(setq currobj (ssadd))
; DRAWING COUPLER
(setq coords (list 
(list 4160.0615 -415) 
(list 4160.0615 -413) 
(list 4233.585 -413) 
(list 4233.585 -413) 
(list 4233.9677 -413.0761) 
(list 4234.2921 -413.2929) 
(list 4234.5089 -413.6173) 
(list 4234.585 -414) 
(list 4234.585 -411.8) 
(list 4234.585 -411.8) 
(list 4234.5089 -412.1827) 
(list 4234.2921 -412.5071) 
(list 4233.9677 -412.7239) 
(list 4233.585 -412.8) 
(list 4160.0615 -412.8) 
(list 4160.0615 -410.8) 
(list 4159.9385 -410.8) 
(list 4159.9385 -412.8) 
(list 4086.415 -412.8) 
(list 4086.0323 -412.7239) 
(list 4085.7079 -412.5071) 
(list 4085.4911 -412.1827) 
(list 4085.415 -411.8) 
(list 4085.415 -411.8) 
(list 4085.415 -414) 
(list 4085.4911 -413.6173) 
(list 4085.7079 -413.2929) 
(list 4086.0323 -413.0761) 
(list 4086.415 -413) 
(list 4086.415 -413) 
(list 4159.9385 -413) 
(list 4159.9385 -415)))
(apply 'command (append '("pline") coords '("c")))
(setq currobj (ssadd (entlast) currobj))
(command "._fillet" "radius" "0.3" "._fillet" "P" (entlast))
(command "_layer" "set" "holes" "")
(command "_circle" "4160,-412.9" "0.113")
(setq currobj (ssadd (entlast) currobj))
(command "_layer" "set" "nitride" "")
(command "_layer" "set" "text" "")
(command "_circle" "4159.2,-415" "0.075")
(command "_circle" "4159.2,-414.7" "0.075")
(command "_circle" "4159.2,-414.4" "0.075")
(command "_circle" "4158.9,-415" "0.075")
(command "_circle" "4158.9,-414.7" "0.075")
(command "_circle" "4158.9,-414.4" "0.075")
(command "_circle" "4158.6,-415" "0.075")
(command "_circle" "4158.6,-414.7" "0.075")
(command "_circle" "4158.6,-414.4" "0.075")
(command "_layer" "set" "nitride" "")
(command "_layer" "set" "prebias" "")
(command "_rectangle" "4085.415,-414" "4234.585,-411.8")
(setq currobj (ssadd (entlast) currobj))
(command "_rectangle" "4159.9385,-415" "4160.0615,-410.8")
(setq currobj (ssadd (entlast) currobj))
(command "_layer" "set" "nitride" "")
(setq coupler13 currobj)
(setq currobj nil)
(setq currobj (ssadd))
; DRAWING SINGLE NANOBEAM
(setq coords (list 
(list 4160.0615 -410.8) 
(list 4160.0615 -409.1417) 
(list 4160.0615 -407.4833) 
(list 4160.0615 -405.825) 
(list 4160.0615 -404.1667) 
(list 4160.0615 -402.5083) 
(list 4160.0615 -400.85) 
(list 4160.0615 -399.1917) 
(list 4160.0615 -397.5333) 
(list 4160.0616 -395.875) 
(list 4160.0616 -394.2167) 
(list 4160.0616 -392.5583) 
(list 4160.0616 -390.9) 
(list 4160.0617 -389.2417) 
(list 4160.0617 -387.5833) 
(list 4160.0617 -385.925) 
(list 4160.0618 -384.2667) 
(list 4160.0619 -382.6083) 
(list 4160.0619 -380.95) 
(list 4160.062 -379.2917) 
(list 4160.0621 -377.6333) 
(list 4160.0622 -375.975) 
(list 4160.0623 -374.3167) 
(list 4160.0624 -372.6583) 
(list 4160.0625 -371) 
(list 4160.0626 -369.3417) 
(list 4160.0628 -367.6833) 
(list 4160.0629 -366.025) 
(list 4160.0631 -364.3667) 
(list 4160.0632 -362.7083) 
(list 4160.0634 -361.05) 
(list 4160.0636 -359.3917) 
(list 4160.0638 -357.7333) 
(list 4160.0641 -356.075) 
(list 4160.0643 -354.4167) 
(list 4160.0646 -352.7583) 
(list 4160.0648 -351.1) 
(list 4160.0651 -349.4417) 
(list 4160.0654 -347.7833) 
(list 4160.0657 -346.125) 
(list 4160.0661 -344.4667) 
(list 4160.0664 -342.8083) 
(list 4160.0668 -341.15) 
(list 4160.0672 -339.4917) 
(list 4160.0676 -337.8333) 
(list 4160.068 -336.175) 
(list 4160.0685 -334.5167) 
(list 4160.0689 -332.8583) 
(list 4160.0694 -331.2) 
(list 4160.0699 -329.5417) 
(list 4160.0704 -327.8833) 
(list 4160.071 -326.225) 
(list 4160.0715 -324.5667) 
(list 4160.0721 -322.9083) 
(list 4160.0728 -321.25) 
(list 4160.0734 -319.5917) 
(list 4160.0741 -317.9333) 
(list 4160.0747 -316.275) 
(list 4160.0754 -314.6167) 
(list 4160.0762 -312.9583) 
(list 4160.0769 -311.3) 
(list 4160.0777 -309.6417) 
(list 4160.0785 -307.9833) 
(list 4160.0794 -306.325) 
(list 4160.0802 -304.6667) 
(list 4160.0811 -303.0083) 
(list 4160.082 -301.35) 
(list 4160.083 -299.6917) 
(list 4160.084 -298.0333) 
(list 4160.085 -296.375) 
(list 4160.086 -294.7167) 
(list 4160.0871 -293.0583) 
(list 4160.0882 -291.4) 
(list 4160.0893 -289.7417) 
(list 4160.0905 -288.0833) 
(list 4160.0917 -286.425) 
(list 4160.0929 -284.7667) 
(list 4160.0941 -283.1083) 
(list 4160.0954 -281.45) 
(list 4160.0967 -279.7917) 
(list 4160.0981 -278.1333) 
(list 4160.0995 -276.475) 
(list 4160.1009 -274.8167) 
(list 4160.1024 -273.1583) 
(list 4160.1039 -271.5) 
(list 4160.1054 -269.8417) 
(list 4160.107 -268.1833) 
(list 4160.1086 -266.525) 
(list 4160.1102 -264.8667) 
(list 4160.1119 -263.2083) 
(list 4160.1136 -261.55) 
(list 4160.1154 -259.8917) 
(list 4160.1172 -258.2333) 
(list 4160.119 -256.575) 
(list 4160.1209 -254.9167) 
(list 4160.1228 -253.2583) 
(list 4160.1247 -251.6) 
(list 4160.1267 -249.9417) 
(list 4160.1288 -248.2833) 
(list 4160.1308 -246.625) 
(list 4160.133 -244.9667) 
(list 4160.1351 -243.3083) 
(list 4160.1373 -241.65) 
(list 4160.1396 -239.9917) 
(list 4160.1419 -238.3333) 
(list 4160.1442 -236.675) 
(list 4160.1466 -235.0167) 
(list 4160.1491 -233.3583) 
(list 4160.1515 -231.7) 
(list 4160.1541 -230.0417) 
(list 4160.1566 -228.3833) 
(list 4160.1592 -226.725) 
(list 4160.1619 -225.0667) 
(list 4160.1646 -223.4083) 
(list 4160.1674 -221.75) 
(list 4160.1702 -220.0917) 
(list 4160.1731 -218.4333) 
(list 4160.176 -216.775) 
(list 4160.1789 -215.1167) 
(list 4160.1819 -213.4583) 
(list 4160.185 -211.8) 
(list 4159.815 -211.8) 
(list 4159.8181 -213.4583) 
(list 4159.8211 -215.1167) 
(list 4159.824 -216.775) 
(list 4159.8269 -218.4333) 
(list 4159.8298 -220.0917) 
(list 4159.8326 -221.75) 
(list 4159.8354 -223.4083) 
(list 4159.8381 -225.0667) 
(list 4159.8408 -226.725) 
(list 4159.8434 -228.3833) 
(list 4159.8459 -230.0417) 
(list 4159.8485 -231.7) 
(list 4159.8509 -233.3583) 
(list 4159.8534 -235.0167) 
(list 4159.8558 -236.675) 
(list 4159.8581 -238.3333) 
(list 4159.8604 -239.9917) 
(list 4159.8627 -241.65) 
(list 4159.8649 -243.3083) 
(list 4159.867 -244.9667) 
(list 4159.8692 -246.625) 
(list 4159.8712 -248.2833) 
(list 4159.8733 -249.9417) 
(list 4159.8753 -251.6) 
(list 4159.8772 -253.2583) 
(list 4159.8791 -254.9167) 
(list 4159.881 -256.575) 
(list 4159.8828 -258.2333) 
(list 4159.8846 -259.8917) 
(list 4159.8864 -261.55) 
(list 4159.8881 -263.2083) 
(list 4159.8898 -264.8667) 
(list 4159.8914 -266.525) 
(list 4159.893 -268.1833) 
(list 4159.8946 -269.8417) 
(list 4159.8961 -271.5) 
(list 4159.8976 -273.1583) 
(list 4159.8991 -274.8167) 
(list 4159.9005 -276.475) 
(list 4159.9019 -278.1333) 
(list 4159.9033 -279.7917) 
(list 4159.9046 -281.45) 
(list 4159.9059 -283.1083) 
(list 4159.9071 -284.7667) 
(list 4159.9083 -286.425) 
(list 4159.9095 -288.0833) 
(list 4159.9107 -289.7417) 
(list 4159.9118 -291.4) 
(list 4159.9129 -293.0583) 
(list 4159.914 -294.7167) 
(list 4159.915 -296.375) 
(list 4159.916 -298.0333) 
(list 4159.917 -299.6917) 
(list 4159.918 -301.35) 
(list 4159.9189 -303.0083) 
(list 4159.9198 -304.6667) 
(list 4159.9206 -306.325) 
(list 4159.9215 -307.9833) 
(list 4159.9223 -309.6417) 
(list 4159.9231 -311.3) 
(list 4159.9238 -312.9583) 
(list 4159.9246 -314.6167) 
(list 4159.9253 -316.275) 
(list 4159.9259 -317.9333) 
(list 4159.9266 -319.5917) 
(list 4159.9272 -321.25) 
(list 4159.9279 -322.9083) 
(list 4159.9285 -324.5667) 
(list 4159.929 -326.225) 
(list 4159.9296 -327.8833) 
(list 4159.9301 -329.5417) 
(list 4159.9306 -331.2) 
(list 4159.9311 -332.8583) 
(list 4159.9315 -334.5167) 
(list 4159.932 -336.175) 
(list 4159.9324 -337.8333) 
(list 4159.9328 -339.4917) 
(list 4159.9332 -341.15) 
(list 4159.9336 -342.8083) 
(list 4159.9339 -344.4667) 
(list 4159.9343 -346.125) 
(list 4159.9346 -347.7833) 
(list 4159.9349 -349.4417) 
(list 4159.9352 -351.1) 
(list 4159.9354 -352.7583) 
(list 4159.9357 -354.4167) 
(list 4159.9359 -356.075) 
(list 4159.9362 -357.7333) 
(list 4159.9364 -359.3917) 
(list 4159.9366 -361.05) 
(list 4159.9368 -362.7083) 
(list 4159.9369 -364.3667) 
(list 4159.9371 -366.025) 
(list 4159.9372 -367.6833) 
(list 4159.9374 -369.3417) 
(list 4159.9375 -371) 
(list 4159.9376 -372.6583) 
(list 4159.9377 -374.3167) 
(list 4159.9378 -375.975) 
(list 4159.9379 -377.6333) 
(list 4159.938 -379.2917) 
(list 4159.9381 -380.95) 
(list 4159.9381 -382.6083) 
(list 4159.9382 -384.2667) 
(list 4159.9383 -385.925) 
(list 4159.9383 -387.5833) 
(list 4159.9383 -389.2417) 
(list 4159.9384 -390.9) 
(list 4159.9384 -392.5583) 
(list 4159.9384 -394.2167) 
(list 4159.9384 -395.875) 
(list 4159.9385 -397.5333) 
(list 4159.9385 -399.1917) 
(list 4159.9385 -400.85) 
(list 4159.9385 -402.5083) 
(list 4159.9385 -404.1667) 
(list 4159.9385 -405.825) 
(list 4159.9385 -407.4833) 
(list 4159.9385 -409.1417) 
(list 4159.9385 -410.8)))
(apply 'command (append '("pline") coords '("c")))
(setq currobj (ssadd (entlast) currobj))
(command "_layer" "set" "prebias" "")
(command "_rectangle" "4159.815,-410.8" "4160.185,-211.8")
(setq currobj (ssadd (entlast) currobj))
(command "_layer" "set" "nitride" "")
(setq singlenanobeam13 currobj)
(setq currobj nil)
(setq currobj (ssadd))
; DRAWING NODE ARRAY
(setq coords (list 
(list 4160.185 -211.8) 
(list 4160.5625 -201.8) 
(list 4160.5625 -201.8) 
(list 4160.5625 -200.8) 
(list 4234.585 -212.6864) 
(list 4234.585 -207.7434) 
(list 4160.5625 -197.357) 
(list 4160.5625 -196.357) 
(list 4160.5625 -196.357) 
(list 4160.2625 -186.357) 
(list 4159.7375 -186.357) 
(list 4159.4375 -196.357) 
(list 4159.4375 -196.357) 
(list 4159.4375 -197.357) 
(list 4085.415 -207.7434) 
(list 4085.415 -212.6864) 
(list 4159.4375 -200.8) 
(list 4159.4375 -201.8) 
(list 4159.4375 -201.8) 
(list 4159.815 -211.8)))
(apply 'command (append '("pline") coords '("c")))
(setq currobj (ssadd (entlast) currobj))
(command "_layer" "set" "prebias" "")
(setq coords (list 
(list 4159.4375 -212.6864) 
(list 4159.4375 -200.8) 
(list 4085.415 -212.6864) 
(list 4085.415 -207.7434) 
(list 4159.4375 -197.357) 
(list 4159.4375 -186.357) 
(list 4160.5625 -186.357) 
(list 4160.5625 -197.357) 
(list 4234.585 -207.7434) 
(list 4234.585 -212.6864) 
(list 4160.5625 -200.8) 
(list 4160.5625 -212.6864)))
(apply 'command (append '("pline") coords '("c")))
(setq currobj (ssadd (entlast) currobj))
(command "_layer" "set" "nitride" "")
(command "_layer" "set" "fda1" "")
(setq coords (list 
(list 4160.5625 -200.657) 
(list 4234.585 -212.5434) 
(list 4234.585 -212.3664) 
(list 4160.5625 -200.58)))
(apply 'command (append '("pline") coords '("c")))
(setq currobj (ssadd (entlast) currobj))
(setq coords (list 
(list 4160.5625 -200.437) 
(list 4234.585 -212.2234) 
(list 4234.585 -212.0464) 
(list 4160.5625 -200.36)))
(apply 'command (append '("pline") coords '("c")))
(setq currobj (ssadd (entlast) currobj))
(setq coords (list 
(list 4160.5625 -200.217) 
(list 4234.585 -211.9034) 
(list 4234.585 -211.7264) 
(list 4160.5625 -200.14)))
(apply 'command (append '("pline") coords '("c")))
(setq currobj (ssadd (entlast) currobj))
(setq coords (list 
(list 4160.5625 -199.997) 
(list 4234.585 -211.5834) 
(list 4234.585 -211.4064) 
(list 4160.5625 -199.92)))
(apply 'command (append '("pline") coords '("c")))
(setq currobj (ssadd (entlast) currobj))
(setq coords (list 
(list 4160.5625 -199.777) 
(list 4234.585 -211.2634) 
(list 4234.585 -211.0864) 
(list 4160.5625 -199.7)))
(apply 'command (append '("pline") coords '("c")))
(setq currobj (ssadd (entlast) currobj))
(setq coords (list 
(list 4160.5625 -199.557) 
(list 4234.585 -210.9434) 
(list 4234.585 -210.7664) 
(list 4160.5625 -199.48)))
(apply 'command (append '("pline") coords '("c")))
(setq currobj (ssadd (entlast) currobj))
(setq coords (list 
(list 4160.5625 -199.337) 
(list 4234.585 -210.6234) 
(list 4234.585 -210.4464) 
(list 4160.5625 -199.26)))
(apply 'command (append '("pline") coords '("c")))
(setq currobj (ssadd (entlast) currobj))
(setq coords (list 
(list 4160.5625 -199.117) 
(list 4234.585 -210.3034) 
(list 4234.585 -210.1264) 
(list 4160.5625 -199.04)))
(apply 'command (append '("pline") coords '("c")))
(setq currobj (ssadd (entlast) currobj))
(setq coords (list 
(list 4160.5625 -198.897) 
(list 4234.585 -209.9834) 
(list 4234.585 -209.8064) 
(list 4160.5625 -198.82)))
(apply 'command (append '("pline") coords '("c")))
(setq currobj (ssadd (entlast) currobj))
(setq coords (list 
(list 4160.5625 -198.677) 
(list 4234.585 -209.6634) 
(list 4234.585 -209.4864) 
(list 4160.5625 -198.6)))
(apply 'command (append '("pline") coords '("c")))
(setq currobj (ssadd (entlast) currobj))
(setq coords (list 
(list 4160.5625 -198.457) 
(list 4234.585 -209.3434) 
(list 4234.585 -209.1664) 
(list 4160.5625 -198.38)))
(apply 'command (append '("pline") coords '("c")))
(setq currobj (ssadd (entlast) currobj))
(setq coords (list 
(list 4160.5625 -198.237) 
(list 4234.585 -209.0234) 
(list 4234.585 -208.8464) 
(list 4160.5625 -198.16)))
(apply 'command (append '("pline") coords '("c")))
(setq currobj (ssadd (entlast) currobj))
(setq coords (list 
(list 4160.5625 -198.017) 
(list 4234.585 -208.7034) 
(list 4234.585 -208.5264) 
(list 4160.5625 -197.94)))
(apply 'command (append '("pline") coords '("c")))
(setq currobj (ssadd (entlast) currobj))
(setq coords (list 
(list 4160.5625 -197.797) 
(list 4234.585 -208.3834) 
(list 4234.585 -208.2064) 
(list 4160.5625 -197.72)))
(apply 'command (append '("pline") coords '("c")))
(setq currobj (ssadd (entlast) currobj))
(setq coords (list 
(list 4160.5625 -197.577) 
(list 4234.585 -208.0634) 
(list 4234.585 -207.8864) 
(list 4160.5625 -197.5)))
(apply 'command (append '("pline") coords '("c")))
(setq currobj (ssadd (entlast) currobj))
(setq coords (list 
(list 4159.4375 -197.5) 
(list 4085.415 -207.8864) 
(list 4085.415 -208.0634) 
(list 4159.4375 -197.577)))
(apply 'command (append '("pline") coords '("c")))
(setq currobj (ssadd (entlast) currobj))
(setq coords (list 
(list 4159.4375 -197.72) 
(list 4085.415 -208.2064) 
(list 4085.415 -208.3834) 
(list 4159.4375 -197.797)))
(apply 'command (append '("pline") coords '("c")))
(setq currobj (ssadd (entlast) currobj))
(setq coords (list 
(list 4159.4375 -197.94) 
(list 4085.415 -208.5264) 
(list 4085.415 -208.7034) 
(list 4159.4375 -198.017)))
(apply 'command (append '("pline") coords '("c")))
(setq currobj (ssadd (entlast) currobj))
(setq coords (list 
(list 4159.4375 -198.16) 
(list 4085.415 -208.8464) 
(list 4085.415 -209.0234) 
(list 4159.4375 -198.237)))
(apply 'command (append '("pline") coords '("c")))
(setq currobj (ssadd (entlast) currobj))
(setq coords (list 
(list 4159.4375 -198.38) 
(list 4085.415 -209.1664) 
(list 4085.415 -209.3434) 
(list 4159.4375 -198.457)))
(apply 'command (append '("pline") coords '("c")))
(setq currobj (ssadd (entlast) currobj))
(setq coords (list 
(list 4159.4375 -198.6) 
(list 4085.415 -209.4864) 
(list 4085.415 -209.6634) 
(list 4159.4375 -198.677)))
(apply 'command (append '("pline") coords '("c")))
(setq currobj (ssadd (entlast) currobj))
(setq coords (list 
(list 4159.4375 -198.82) 
(list 4085.415 -209.8064) 
(list 4085.415 -209.9834) 
(list 4159.4375 -198.897)))
(apply 'command (append '("pline") coords '("c")))
(setq currobj (ssadd (entlast) currobj))
(setq coords (list 
(list 4159.4375 -199.04) 
(list 4085.415 -210.1264) 
(list 4085.415 -210.3034) 
(list 4159.4375 -199.117)))
(apply 'command (append '("pline") coords '("c")))
(setq currobj (ssadd (entlast) currobj))
(setq coords (list 
(list 4159.4375 -199.26) 
(list 4085.415 -210.4464) 
(list 4085.415 -210.6234) 
(list 4159.4375 -199.337)))
(apply 'command (append '("pline") coords '("c")))
(setq currobj (ssadd (entlast) currobj))
(setq coords (list 
(list 4159.4375 -199.48) 
(list 4085.415 -210.7664) 
(list 4085.415 -210.9434) 
(list 4159.4375 -199.557)))
(apply 'command (append '("pline") coords '("c")))
(setq currobj (ssadd (entlast) currobj))
(setq coords (list 
(list 4159.4375 -199.7) 
(list 4085.415 -211.0864) 
(list 4085.415 -211.2634) 
(list 4159.4375 -199.777)))
(apply 'command (append '("pline") coords '("c")))
(setq currobj (ssadd (entlast) currobj))
(setq coords (list 
(list 4159.4375 -199.92) 
(list 4085.415 -211.4064) 
(list 4085.415 -211.5834) 
(list 4159.4375 -199.997)))
(apply 'command (append '("pline") coords '("c")))
(setq currobj (ssadd (entlast) currobj))
(setq coords (list 
(list 4159.4375 -200.14) 
(list 4085.415 -211.7264) 
(list 4085.415 -211.9034) 
(list 4159.4375 -200.217)))
(apply 'command (append '("pline") coords '("c")))
(setq currobj (ssadd (entlast) currobj))
(setq coords (list 
(list 4159.4375 -200.36) 
(list 4085.415 -212.0464) 
(list 4085.415 -212.2234) 
(list 4159.4375 -200.437)))
(apply 'command (append '("pline") coords '("c")))
(setq currobj (ssadd (entlast) currobj))
(setq coords (list 
(list 4159.4375 -200.58) 
(list 4085.415 -212.3664) 
(list 4085.415 -212.5434) 
(list 4159.4375 -200.657)))
(apply 'command (append '("pline") coords '("c")))
(setq currobj (ssadd (entlast) currobj))
(command "_layer" "set" "nitride" "")
(command "_layer" "set" "text" "")
(command "_circle" "4158.985,-211.8" "0.075")
(command "_circle" "4158.985,-211.5" "0.075")
(command "_circle" "4158.985,-211.2" "0.075")
(command "_circle" "4158.985,-210.9" "0.075")
(command "_circle" "4158.985,-210.6" "0.075")
(command "_circle" "4158.685,-211.8" "0.075")
(command "_circle" "4158.685,-211.5" "0.075")
(command "_circle" "4158.685,-211.2" "0.075")
(command "_circle" "4158.685,-210.9" "0.075")
(command "_circle" "4158.685,-210.6" "0.075")
(command "_circle" "4158.385,-211.8" "0.075")
(command "_circle" "4158.385,-211.5" "0.075")
(command "_circle" "4158.385,-211.2" "0.075")
(command "_circle" "4158.385,-210.9" "0.075")
(command "_circle" "4158.385,-210.6" "0.075")
(command "_circle" "4158.085,-211.8" "0.075")
(command "_circle" "4158.085,-211.5" "0.075")
(command "_circle" "4158.085,-211.2" "0.075")
(command "_circle" "4158.085,-210.9" "0.075")
(command "_circle" "4158.085,-210.6" "0.075")
(command "_circle" "4157.785,-211.8" "0.075")
(command "_circle" "4157.785,-211.5" "0.075")
(command "_circle" "4157.785,-211.2" "0.075")
(command "_circle" "4157.785,-210.9" "0.075")
(command "_circle" "4157.785,-210.6" "0.075")
(command "_layer" "set" "nitride" "")
(setq anglednodearray13 currobj)
(setq currobj nil)
(setq currobj (ssadd))
; DRAWING COOLED SINGLE NANOBEAM
(setq coords (list 
(list 4160.2625 -186.357) 
(list 4160.2625 -181.357) 
(list 4159.7375 -181.357) 
(list 4159.7375 -186.357)))
(apply 'command (append '("pline") coords '("c")))
(setq currobj (ssadd (entlast) currobj))
(command "_layer" "set" "prebias" "")
(command "_rectangle" "4159.7375,-186.357" "4160.2625,-181.357")
(setq currobj (ssadd (entlast) currobj))
(command "_layer" "set" "nitride" "")
(setq coords (list 
(list 4160.2625 -181.357) 
(list 4160.5625 -171.357) 
(list 4160.5625 -171.357) 
(list 4160.5625 -170.357) 
(list 4234.585 -171.107) 
(list 4234.585 -166.164) 
(list 4160.5625 -166.914) 
(list 4160.5625 -165.914) 
(list 4160.5625 -165.914) 
(list 4160.2625 -155.914) 
(list 4159.7375 -155.914) 
(list 4159.4375 -165.914) 
(list 4159.4375 -165.914) 
(list 4159.4375 -166.914) 
(list 4085.415 -166.164) 
(list 4085.415 -171.107) 
(list 4159.4375 -170.357) 
(list 4159.4375 -171.357) 
(list 4159.4375 -171.357) 
(list 4159.7375 -181.357)))
(apply 'command (append '("pline") coords '("c")))
(setq currobj (ssadd (entlast) currobj))
(command "_layer" "set" "prebias" "")
(setq coords (list 
(list 4159.4375 -181.357) 
(list 4159.4375 -170.357) 
(list 4085.415 -171.107) 
(list 4085.415 -166.164) 
(list 4159.4375 -166.914) 
(list 4159.4375 -155.914) 
(list 4160.5625 -155.914) 
(list 4160.5625 -166.914) 
(list 4234.585 -166.164) 
(list 4234.585 -171.107) 
(list 4160.5625 -170.357) 
(list 4160.5625 -181.357)))
(apply 'command (append '("pline") coords '("c")))
(setq currobj (ssadd (entlast) currobj))
(command "_layer" "set" "nitride" "")
(command "_layer" "set" "fda1" "")
(setq coords (list 
(list 4160.5625 -170.214) 
(list 4234.585 -170.964) 
(list 4234.585 -170.787) 
(list 4160.5625 -170.137)))
(apply 'command (append '("pline") coords '("c")))
(setq currobj (ssadd (entlast) currobj))
(setq coords (list 
(list 4160.5625 -169.994) 
(list 4234.585 -170.644) 
(list 4234.585 -170.467) 
(list 4160.5625 -169.917)))
(apply 'command (append '("pline") coords '("c")))
(setq currobj (ssadd (entlast) currobj))
(setq coords (list 
(list 4160.5625 -169.774) 
(list 4234.585 -170.324) 
(list 4234.585 -170.147) 
(list 4160.5625 -169.697)))
(apply 'command (append '("pline") coords '("c")))
(setq currobj (ssadd (entlast) currobj))
(setq coords (list 
(list 4160.5625 -169.554) 
(list 4234.585 -170.004) 
(list 4234.585 -169.827) 
(list 4160.5625 -169.477)))
(apply 'command (append '("pline") coords '("c")))
(setq currobj (ssadd (entlast) currobj))
(setq coords (list 
(list 4160.5625 -169.334) 
(list 4234.585 -169.684) 
(list 4234.585 -169.507) 
(list 4160.5625 -169.257)))
(apply 'command (append '("pline") coords '("c")))
(setq currobj (ssadd (entlast) currobj))
(setq coords (list 
(list 4160.5625 -169.114) 
(list 4234.585 -169.364) 
(list 4234.585 -169.187) 
(list 4160.5625 -169.037)))
(apply 'command (append '("pline") coords '("c")))
(setq currobj (ssadd (entlast) currobj))
(setq coords (list 
(list 4160.5625 -168.894) 
(list 4234.585 -169.044) 
(list 4234.585 -168.867) 
(list 4160.5625 -168.817)))
(apply 'command (append '("pline") coords '("c")))
(setq currobj (ssadd (entlast) currobj))
(setq coords (list 
(list 4160.5625 -168.674) 
(list 4234.585 -168.724) 
(list 4234.585 -168.547) 
(list 4160.5625 -168.597)))
(apply 'command (append '("pline") coords '("c")))
(setq currobj (ssadd (entlast) currobj))
(setq coords (list 
(list 4160.5625 -168.454) 
(list 4234.585 -168.404) 
(list 4234.585 -168.227) 
(list 4160.5625 -168.377)))
(apply 'command (append '("pline") coords '("c")))
(setq currobj (ssadd (entlast) currobj))
(setq coords (list 
(list 4160.5625 -168.234) 
(list 4234.585 -168.084) 
(list 4234.585 -167.907) 
(list 4160.5625 -168.157)))
(apply 'command (append '("pline") coords '("c")))
(setq currobj (ssadd (entlast) currobj))
(setq coords (list 
(list 4160.5625 -168.014) 
(list 4234.585 -167.764) 
(list 4234.585 -167.587) 
(list 4160.5625 -167.937)))
(apply 'command (append '("pline") coords '("c")))
(setq currobj (ssadd (entlast) currobj))
(setq coords (list 
(list 4160.5625 -167.794) 
(list 4234.585 -167.444) 
(list 4234.585 -167.267) 
(list 4160.5625 -167.717)))
(apply 'command (append '("pline") coords '("c")))
(setq currobj (ssadd (entlast) currobj))
(setq coords (list 
(list 4160.5625 -167.574) 
(list 4234.585 -167.124) 
(list 4234.585 -166.947) 
(list 4160.5625 -167.497)))
(apply 'command (append '("pline") coords '("c")))
(setq currobj (ssadd (entlast) currobj))
(setq coords (list 
(list 4160.5625 -167.354) 
(list 4234.585 -166.804) 
(list 4234.585 -166.627) 
(list 4160.5625 -167.277)))
(apply 'command (append '("pline") coords '("c")))
(setq currobj (ssadd (entlast) currobj))
(setq coords (list 
(list 4160.5625 -167.134) 
(list 4234.585 -166.484) 
(list 4234.585 -166.307) 
(list 4160.5625 -167.057)))
(apply 'command (append '("pline") coords '("c")))
(setq currobj (ssadd (entlast) currobj))
(setq coords (list 
(list 4159.4375 -167.057) 
(list 4085.415 -166.307) 
(list 4085.415 -166.484) 
(list 4159.4375 -167.134)))
(apply 'command (append '("pline") coords '("c")))
(setq currobj (ssadd (entlast) currobj))
(setq coords (list 
(list 4159.4375 -167.277) 
(list 4085.415 -166.627) 
(list 4085.415 -166.804) 
(list 4159.4375 -167.354)))
(apply 'command (append '("pline") coords '("c")))
(setq currobj (ssadd (entlast) currobj))
(setq coords (list 
(list 4159.4375 -167.497) 
(list 4085.415 -166.947) 
(list 4085.415 -167.124) 
(list 4159.4375 -167.574)))
(apply 'command (append '("pline") coords '("c")))
(setq currobj (ssadd (entlast) currobj))
(setq coords (list 
(list 4159.4375 -167.717) 
(list 4085.415 -167.267) 
(list 4085.415 -167.444) 
(list 4159.4375 -167.794)))
(apply 'command (append '("pline") coords '("c")))
(setq currobj (ssadd (entlast) currobj))
(setq coords (list 
(list 4159.4375 -167.937) 
(list 4085.415 -167.587) 
(list 4085.415 -167.764) 
(list 4159.4375 -168.014)))
(apply 'command (append '("pline") coords '("c")))
(setq currobj (ssadd (entlast) currobj))
(setq coords (list 
(list 4159.4375 -168.157) 
(list 4085.415 -167.907) 
(list 4085.415 -168.084) 
(list 4159.4375 -168.234)))
(apply 'command (append '("pline") coords '("c")))
(setq currobj (ssadd (entlast) currobj))
(setq coords (list 
(list 4159.4375 -168.377) 
(list 4085.415 -168.227) 
(list 4085.415 -168.404) 
(list 4159.4375 -168.454)))
(apply 'command (append '("pline") coords '("c")))
(setq currobj (ssadd (entlast) currobj))
(setq coords (list 
(list 4159.4375 -168.597) 
(list 4085.415 -168.547) 
(list 4085.415 -168.724) 
(list 4159.4375 -168.674)))
(apply 'command (append '("pline") coords '("c")))
(setq currobj (ssadd (entlast) currobj))
(setq coords (list 
(list 4159.4375 -168.817) 
(list 4085.415 -168.867) 
(list 4085.415 -169.044) 
(list 4159.4375 -168.894)))
(apply 'command (append '("pline") coords '("c")))
(setq currobj (ssadd (entlast) currobj))
(setq coords (list 
(list 4159.4375 -169.037) 
(list 4085.415 -169.187) 
(list 4085.415 -169.364) 
(list 4159.4375 -169.114)))
(apply 'command (append '("pline") coords '("c")))
(setq currobj (ssadd (entlast) currobj))
(setq coords (list 
(list 4159.4375 -169.257) 
(list 4085.415 -169.507) 
(list 4085.415 -169.684) 
(list 4159.4375 -169.334)))
(apply 'command (append '("pline") coords '("c")))
(setq currobj (ssadd (entlast) currobj))
(setq coords (list 
(list 4159.4375 -169.477) 
(list 4085.415 -169.827) 
(list 4085.415 -170.004) 
(list 4159.4375 -169.554)))
(apply 'command (append '("pline") coords '("c")))
(setq currobj (ssadd (entlast) currobj))
(setq coords (list 
(list 4159.4375 -169.697) 
(list 4085.415 -170.147) 
(list 4085.415 -170.324) 
(list 4159.4375 -169.774)))
(apply 'command (append '("pline") coords '("c")))
(setq currobj (ssadd (entlast) currobj))
(setq coords (list 
(list 4159.4375 -169.917) 
(list 4085.415 -170.467) 
(list 4085.415 -170.644) 
(list 4159.4375 -169.994)))
(apply 'command (append '("pline") coords '("c")))
(setq currobj (ssadd (entlast) currobj))
(setq coords (list 
(list 4159.4375 -170.137) 
(list 4085.415 -170.787) 
(list 4085.415 -170.964) 
(list 4159.4375 -170.214)))
(apply 'command (append '("pline") coords '("c")))
(setq currobj (ssadd (entlast) currobj))
(command "_layer" "set" "nitride" "")
(command "_layer" "set" "text" "")
(command "_circle" "4159.0625,-181.357" "0.075")
(command "_circle" "4159.0625,-181.057" "0.075")
(command "_circle" "4159.0625,-180.757" "0.075")
(command "_circle" "4159.0625,-180.457" "0.075")
(command "_circle" "4159.0625,-180.157" "0.075")
(command "_circle" "4158.7625,-181.357" "0.075")
(command "_circle" "4158.7625,-181.057" "0.075")
(command "_circle" "4158.7625,-180.757" "0.075")
(command "_circle" "4158.7625,-180.457" "0.075")
(command "_circle" "4158.7625,-180.157" "0.075")
(command "_circle" "4158.4625,-181.357" "0.075")
(command "_circle" "4158.4625,-181.057" "0.075")
(command "_circle" "4158.4625,-180.757" "0.075")
(command "_circle" "4158.4625,-180.457" "0.075")
(command "_circle" "4158.4625,-180.157" "0.075")
(command "_circle" "4158.1625,-181.357" "0.075")
(command "_circle" "4158.1625,-181.057" "0.075")
(command "_circle" "4158.1625,-180.757" "0.075")
(command "_circle" "4158.1625,-180.457" "0.075")
(command "_circle" "4158.1625,-180.157" "0.075")
(command "_circle" "4157.8625,-181.357" "0.075")
(command "_circle" "4157.8625,-181.057" "0.075")
(command "_circle" "4157.8625,-180.757" "0.075")
(command "_circle" "4157.8625,-180.457" "0.075")
(command "_circle" "4157.8625,-180.157" "0.075")
(command "_layer" "set" "nitride" "")
(setq coords (list 
(list 4160.2625 -155.914) 
(list 4160.2625 -40.2693) 
(list 4159.7375 -40.2693) 
(list 4159.7375 -155.914)))
(apply 'command (append '("pline") coords '("c")))
(setq currobj (ssadd (entlast) currobj))
(command "_layer" "set" "prebias" "")
(command "_rectangle" "4159.7375,-155.914" "4160.2625,-40.2693")
(setq currobj (ssadd (entlast) currobj))
(command "_layer" "set" "nitride" "")
(setq coords (list 
(list 4160.2625 -40.2693) 
(list 4160.5625 -30.2693) 
(list 4160.5625 -30.2693) 
(list 4160.5625 -29.2693) 
(list 4234.585 -30.0193) 
(list 4234.585 -25.0763) 
(list 4160.5625 -25.8263) 
(list 4160.5625 -24.8263) 
(list 4160.5625 -24.8263) 
(list 4160.2625 -14.8263) 
(list 4159.7375 -14.8263) 
(list 4159.4375 -24.8263) 
(list 4159.4375 -24.8263) 
(list 4159.4375 -25.8263) 
(list 4085.415 -25.0763) 
(list 4085.415 -30.0193) 
(list 4159.4375 -29.2693) 
(list 4159.4375 -30.2693) 
(list 4159.4375 -30.2693) 
(list 4159.7375 -40.2693)))
(apply 'command (append '("pline") coords '("c")))
(setq currobj (ssadd (entlast) currobj))
(command "_layer" "set" "prebias" "")
(setq coords (list 
(list 4159.4375 -40.2693) 
(list 4159.4375 -29.2693) 
(list 4085.415 -30.0193) 
(list 4085.415 -25.0763) 
(list 4159.4375 -25.8263) 
(list 4159.4375 -14.8263) 
(list 4160.5625 -14.8263) 
(list 4160.5625 -25.8263) 
(list 4234.585 -25.0763) 
(list 4234.585 -30.0193) 
(list 4160.5625 -29.2693) 
(list 4160.5625 -40.2693)))
(apply 'command (append '("pline") coords '("c")))
(setq currobj (ssadd (entlast) currobj))
(command "_layer" "set" "nitride" "")
(command "_layer" "set" "fda1" "")
(setq coords (list 
(list 4160.5625 -29.1263) 
(list 4234.585 -29.8763) 
(list 4234.585 -29.6993) 
(list 4160.5625 -29.0493)))
(apply 'command (append '("pline") coords '("c")))
(setq currobj (ssadd (entlast) currobj))
(setq coords (list 
(list 4160.5625 -28.9063) 
(list 4234.585 -29.5563) 
(list 4234.585 -29.3793) 
(list 4160.5625 -28.8293)))
(apply 'command (append '("pline") coords '("c")))
(setq currobj (ssadd (entlast) currobj))
(setq coords (list 
(list 4160.5625 -28.6863) 
(list 4234.585 -29.2363) 
(list 4234.585 -29.0593) 
(list 4160.5625 -28.6093)))
(apply 'command (append '("pline") coords '("c")))
(setq currobj (ssadd (entlast) currobj))
(setq coords (list 
(list 4160.5625 -28.4663) 
(list 4234.585 -28.9163) 
(list 4234.585 -28.7393) 
(list 4160.5625 -28.3893)))
(apply 'command (append '("pline") coords '("c")))
(setq currobj (ssadd (entlast) currobj))
(setq coords (list 
(list 4160.5625 -28.2463) 
(list 4234.585 -28.5963) 
(list 4234.585 -28.4193) 
(list 4160.5625 -28.1693)))
(apply 'command (append '("pline") coords '("c")))
(setq currobj (ssadd (entlast) currobj))
(setq coords (list 
(list 4160.5625 -28.0263) 
(list 4234.585 -28.2763) 
(list 4234.585 -28.0993) 
(list 4160.5625 -27.9493)))
(apply 'command (append '("pline") coords '("c")))
(setq currobj (ssadd (entlast) currobj))
(setq coords (list 
(list 4160.5625 -27.8063) 
(list 4234.585 -27.9563) 
(list 4234.585 -27.7793) 
(list 4160.5625 -27.7293)))
(apply 'command (append '("pline") coords '("c")))
(setq currobj (ssadd (entlast) currobj))
(setq coords (list 
(list 4160.5625 -27.5863) 
(list 4234.585 -27.6363) 
(list 4234.585 -27.4593) 
(list 4160.5625 -27.5093)))
(apply 'command (append '("pline") coords '("c")))
(setq currobj (ssadd (entlast) currobj))
(setq coords (list 
(list 4160.5625 -27.3663) 
(list 4234.585 -27.3163) 
(list 4234.585 -27.1393) 
(list 4160.5625 -27.2893)))
(apply 'command (append '("pline") coords '("c")))
(setq currobj (ssadd (entlast) currobj))
(setq coords (list 
(list 4160.5625 -27.1463) 
(list 4234.585 -26.9963) 
(list 4234.585 -26.8193) 
(list 4160.5625 -27.0693)))
(apply 'command (append '("pline") coords '("c")))
(setq currobj (ssadd (entlast) currobj))
(setq coords (list 
(list 4160.5625 -26.9263) 
(list 4234.585 -26.6763) 
(list 4234.585 -26.4993) 
(list 4160.5625 -26.8493)))
(apply 'command (append '("pline") coords '("c")))
(setq currobj (ssadd (entlast) currobj))
(setq coords (list 
(list 4160.5625 -26.7063) 
(list 4234.585 -26.3563) 
(list 4234.585 -26.1793) 
(list 4160.5625 -26.6293)))
(apply 'command (append '("pline") coords '("c")))
(setq currobj (ssadd (entlast) currobj))
(setq coords (list 
(list 4160.5625 -26.4863) 
(list 4234.585 -26.0363) 
(list 4234.585 -25.8593) 
(list 4160.5625 -26.4093)))
(apply 'command (append '("pline") coords '("c")))
(setq currobj (ssadd (entlast) currobj))
(setq coords (list 
(list 4160.5625 -26.2663) 
(list 4234.585 -25.7163) 
(list 4234.585 -25.5393) 
(list 4160.5625 -26.1893)))
(apply 'command (append '("pline") coords '("c")))
(setq currobj (ssadd (entlast) currobj))
(setq coords (list 
(list 4160.5625 -26.0463) 
(list 4234.585 -25.3963) 
(list 4234.585 -25.2193) 
(list 4160.5625 -25.9693)))
(apply 'command (append '("pline") coords '("c")))
(setq currobj (ssadd (entlast) currobj))
(setq coords (list 
(list 4159.4375 -25.9693) 
(list 4085.415 -25.2193) 
(list 4085.415 -25.3963) 
(list 4159.4375 -26.0463)))
(apply 'command (append '("pline") coords '("c")))
(setq currobj (ssadd (entlast) currobj))
(setq coords (list 
(list 4159.4375 -26.1893) 
(list 4085.415 -25.5393) 
(list 4085.415 -25.7163) 
(list 4159.4375 -26.2663)))
(apply 'command (append '("pline") coords '("c")))
(setq currobj (ssadd (entlast) currobj))
(setq coords (list 
(list 4159.4375 -26.4093) 
(list 4085.415 -25.8593) 
(list 4085.415 -26.0363) 
(list 4159.4375 -26.4863)))
(apply 'command (append '("pline") coords '("c")))
(setq currobj (ssadd (entlast) currobj))
(setq coords (list 
(list 4159.4375 -26.6293) 
(list 4085.415 -26.1793) 
(list 4085.415 -26.3563) 
(list 4159.4375 -26.7063)))
(apply 'command (append '("pline") coords '("c")))
(setq currobj (ssadd (entlast) currobj))
(setq coords (list 
(list 4159.4375 -26.8493) 
(list 4085.415 -26.4993) 
(list 4085.415 -26.6763) 
(list 4159.4375 -26.9263)))
(apply 'command (append '("pline") coords '("c")))
(setq currobj (ssadd (entlast) currobj))
(setq coords (list 
(list 4159.4375 -27.0693) 
(list 4085.415 -26.8193) 
(list 4085.415 -26.9963) 
(list 4159.4375 -27.1463)))
(apply 'command (append '("pline") coords '("c")))
(setq currobj (ssadd (entlast) currobj))
(setq coords (list 
(list 4159.4375 -27.2893) 
(list 4085.415 -27.1393) 
(list 4085.415 -27.3163) 
(list 4159.4375 -27.3663)))
(apply 'command (append '("pline") coords '("c")))
(setq currobj (ssadd (entlast) currobj))
(setq coords (list 
(list 4159.4375 -27.5093) 
(list 4085.415 -27.4593) 
(list 4085.415 -27.6363) 
(list 4159.4375 -27.5863)))
(apply 'command (append '("pline") coords '("c")))
(setq currobj (ssadd (entlast) currobj))
(setq coords (list 
(list 4159.4375 -27.7293) 
(list 4085.415 -27.7793) 
(list 4085.415 -27.9563) 
(list 4159.4375 -27.8063)))
(apply 'command (append '("pline") coords '("c")))
(setq currobj (ssadd (entlast) currobj))
(setq coords (list 
(list 4159.4375 -27.9493) 
(list 4085.415 -28.0993) 
(list 4085.415 -28.2763) 
(list 4159.4375 -28.0263)))
(apply 'command (append '("pline") coords '("c")))
(setq currobj (ssadd (entlast) currobj))
(setq coords (list 
(list 4159.4375 -28.1693) 
(list 4085.415 -28.4193) 
(list 4085.415 -28.5963) 
(list 4159.4375 -28.2463)))
(apply 'command (append '("pline") coords '("c")))
(setq currobj (ssadd (entlast) currobj))
(setq coords (list 
(list 4159.4375 -28.3893) 
(list 4085.415 -28.7393) 
(list 4085.415 -28.9163) 
(list 4159.4375 -28.4663)))
(apply 'command (append '("pline") coords '("c")))
(setq currobj (ssadd (entlast) currobj))
(setq coords (list 
(list 4159.4375 -28.6093) 
(list 4085.415 -29.0593) 
(list 4085.415 -29.2363) 
(list 4159.4375 -28.6863)))
(apply 'command (append '("pline") coords '("c")))
(setq currobj (ssadd (entlast) currobj))
(setq coords (list 
(list 4159.4375 -28.8293) 
(list 4085.415 -29.3793) 
(list 4085.415 -29.5563) 
(list 4159.4375 -28.9063)))
(apply 'command (append '("pline") coords '("c")))
(setq currobj (ssadd (entlast) currobj))
(setq coords (list 
(list 4159.4375 -29.0493) 
(list 4085.415 -29.6993) 
(list 4085.415 -29.8763) 
(list 4159.4375 -29.1263)))
(apply 'command (append '("pline") coords '("c")))
(setq currobj (ssadd (entlast) currobj))
(command "_layer" "set" "nitride" "")
(command "_layer" "set" "text" "")
(command "_circle" "4159.0625,-40.2693" "0.075")
(command "_circle" "4159.0625,-39.9693" "0.075")
(command "_circle" "4159.0625,-39.6693" "0.075")
(command "_circle" "4159.0625,-39.3693" "0.075")
(command "_circle" "4159.0625,-39.0693" "0.075")
(command "_circle" "4158.7625,-40.2693" "0.075")
(command "_circle" "4158.7625,-39.9693" "0.075")
(command "_circle" "4158.7625,-39.6693" "0.075")
(command "_circle" "4158.7625,-39.3693" "0.075")
(command "_circle" "4158.7625,-39.0693" "0.075")
(command "_circle" "4158.4625,-40.2693" "0.075")
(command "_circle" "4158.4625,-39.9693" "0.075")
(command "_circle" "4158.4625,-39.6693" "0.075")
(command "_circle" "4158.4625,-39.3693" "0.075")
(command "_circle" "4158.4625,-39.0693" "0.075")
(command "_circle" "4158.1625,-40.2693" "0.075")
(command "_circle" "4158.1625,-39.9693" "0.075")
(command "_circle" "4158.1625,-39.6693" "0.075")
(command "_circle" "4158.1625,-39.3693" "0.075")
(command "_circle" "4158.1625,-39.0693" "0.075")
(command "_circle" "4157.8625,-40.2693" "0.075")
(command "_circle" "4157.8625,-39.9693" "0.075")
(command "_circle" "4157.8625,-39.6693" "0.075")
(command "_circle" "4157.8625,-39.3693" "0.075")
(command "_circle" "4157.8625,-39.0693" "0.075")
(command "_layer" "set" "nitride" "")
(setq coords (list 
(list 4160.2625 -14.8263) 
(list 4160.2625 100.8184) 
(list 4159.7375 100.8184) 
(list 4159.7375 -14.8263)))
(apply 'command (append '("pline") coords '("c")))
(setq currobj (ssadd (entlast) currobj))
(command "_layer" "set" "prebias" "")
(command "_rectangle" "4159.7375,-14.8263" "4160.2625,100.8184")
(setq currobj (ssadd (entlast) currobj))
(command "_layer" "set" "nitride" "")
(setq coords (list 
(list 4160.2625 100.8184) 
(list 4160.5625 110.8184) 
(list 4160.5625 110.8184) 
(list 4160.5625 111.8184) 
(list 4234.585 111.0684) 
(list 4234.585 116.0114) 
(list 4160.5625 115.2614) 
(list 4160.5625 116.2614) 
(list 4160.5625 116.2614) 
(list 4160.2625 126.2614) 
(list 4159.7375 126.2614) 
(list 4159.4375 116.2614) 
(list 4159.4375 116.2614) 
(list 4159.4375 115.2614) 
(list 4085.415 116.0114) 
(list 4085.415 111.0684) 
(list 4159.4375 111.8184) 
(list 4159.4375 110.8184) 
(list 4159.4375 110.8184) 
(list 4159.7375 100.8184)))
(apply 'command (append '("pline") coords '("c")))
(setq currobj (ssadd (entlast) currobj))
(command "_layer" "set" "prebias" "")
(setq coords (list 
(list 4159.4375 100.8184) 
(list 4159.4375 111.8184) 
(list 4085.415 111.0684) 
(list 4085.415 116.0114) 
(list 4159.4375 115.2614) 
(list 4159.4375 126.2614) 
(list 4160.5625 126.2614) 
(list 4160.5625 115.2614) 
(list 4234.585 116.0114) 
(list 4234.585 111.0684) 
(list 4160.5625 111.8184) 
(list 4160.5625 100.8184)))
(apply 'command (append '("pline") coords '("c")))
(setq currobj (ssadd (entlast) currobj))
(command "_layer" "set" "nitride" "")
(command "_layer" "set" "fda1" "")
(setq coords (list 
(list 4160.5625 111.9614) 
(list 4234.585 111.2114) 
(list 4234.585 111.3884) 
(list 4160.5625 112.0384)))
(apply 'command (append '("pline") coords '("c")))
(setq currobj (ssadd (entlast) currobj))
(setq coords (list 
(list 4160.5625 112.1814) 
(list 4234.585 111.5314) 
(list 4234.585 111.7084) 
(list 4160.5625 112.2584)))
(apply 'command (append '("pline") coords '("c")))
(setq currobj (ssadd (entlast) currobj))
(setq coords (list 
(list 4160.5625 112.4014) 
(list 4234.585 111.8514) 
(list 4234.585 112.0284) 
(list 4160.5625 112.4784)))
(apply 'command (append '("pline") coords '("c")))
(setq currobj (ssadd (entlast) currobj))
(setq coords (list 
(list 4160.5625 112.6214) 
(list 4234.585 112.1714) 
(list 4234.585 112.3484) 
(list 4160.5625 112.6984)))
(apply 'command (append '("pline") coords '("c")))
(setq currobj (ssadd (entlast) currobj))
(setq coords (list 
(list 4160.5625 112.8414) 
(list 4234.585 112.4914) 
(list 4234.585 112.6684) 
(list 4160.5625 112.9184)))
(apply 'command (append '("pline") coords '("c")))
(setq currobj (ssadd (entlast) currobj))
(setq coords (list 
(list 4160.5625 113.0614) 
(list 4234.585 112.8114) 
(list 4234.585 112.9884) 
(list 4160.5625 113.1384)))
(apply 'command (append '("pline") coords '("c")))
(setq currobj (ssadd (entlast) currobj))
(setq coords (list 
(list 4160.5625 113.2814) 
(list 4234.585 113.1314) 
(list 4234.585 113.3084) 
(list 4160.5625 113.3584)))
(apply 'command (append '("pline") coords '("c")))
(setq currobj (ssadd (entlast) currobj))
(setq coords (list 
(list 4160.5625 113.5014) 
(list 4234.585 113.4514) 
(list 4234.585 113.6284) 
(list 4160.5625 113.5784)))
(apply 'command (append '("pline") coords '("c")))
(setq currobj (ssadd (entlast) currobj))
(setq coords (list 
(list 4160.5625 113.7214) 
(list 4234.585 113.7714) 
(list 4234.585 113.9484) 
(list 4160.5625 113.7984)))
(apply 'command (append '("pline") coords '("c")))
(setq currobj (ssadd (entlast) currobj))
(setq coords (list 
(list 4160.5625 113.9414) 
(list 4234.585 114.0914) 
(list 4234.585 114.2684) 
(list 4160.5625 114.0184)))
(apply 'command (append '("pline") coords '("c")))
(setq currobj (ssadd (entlast) currobj))
(setq coords (list 
(list 4160.5625 114.1614) 
(list 4234.585 114.4114) 
(list 4234.585 114.5884) 
(list 4160.5625 114.2384)))
(apply 'command (append '("pline") coords '("c")))
(setq currobj (ssadd (entlast) currobj))
(setq coords (list 
(list 4160.5625 114.3814) 
(list 4234.585 114.7314) 
(list 4234.585 114.9084) 
(list 4160.5625 114.4584)))
(apply 'command (append '("pline") coords '("c")))
(setq currobj (ssadd (entlast) currobj))
(setq coords (list 
(list 4160.5625 114.6014) 
(list 4234.585 115.0514) 
(list 4234.585 115.2284) 
(list 4160.5625 114.6784)))
(apply 'command (append '("pline") coords '("c")))
(setq currobj (ssadd (entlast) currobj))
(setq coords (list 
(list 4160.5625 114.8214) 
(list 4234.585 115.3714) 
(list 4234.585 115.5484) 
(list 4160.5625 114.8984)))
(apply 'command (append '("pline") coords '("c")))
(setq currobj (ssadd (entlast) currobj))
(setq coords (list 
(list 4160.5625 115.0414) 
(list 4234.585 115.6914) 
(list 4234.585 115.8684) 
(list 4160.5625 115.1184)))
(apply 'command (append '("pline") coords '("c")))
(setq currobj (ssadd (entlast) currobj))
(setq coords (list 
(list 4159.4375 115.1184) 
(list 4085.415 115.8684) 
(list 4085.415 115.6914) 
(list 4159.4375 115.0414)))
(apply 'command (append '("pline") coords '("c")))
(setq currobj (ssadd (entlast) currobj))
(setq coords (list 
(list 4159.4375 114.8984) 
(list 4085.415 115.5484) 
(list 4085.415 115.3714) 
(list 4159.4375 114.8214)))
(apply 'command (append '("pline") coords '("c")))
(setq currobj (ssadd (entlast) currobj))
(setq coords (list 
(list 4159.4375 114.6784) 
(list 4085.415 115.2284) 
(list 4085.415 115.0514) 
(list 4159.4375 114.6014)))
(apply 'command (append '("pline") coords '("c")))
(setq currobj (ssadd (entlast) currobj))
(setq coords (list 
(list 4159.4375 114.4584) 
(list 4085.415 114.9084) 
(list 4085.415 114.7314) 
(list 4159.4375 114.3814)))
(apply 'command (append '("pline") coords '("c")))
(setq currobj (ssadd (entlast) currobj))
(setq coords (list 
(list 4159.4375 114.2384) 
(list 4085.415 114.5884) 
(list 4085.415 114.4114) 
(list 4159.4375 114.1614)))
(apply 'command (append '("pline") coords '("c")))
(setq currobj (ssadd (entlast) currobj))
(setq coords (list 
(list 4159.4375 114.0184) 
(list 4085.415 114.2684) 
(list 4085.415 114.0914) 
(list 4159.4375 113.9414)))
(apply 'command (append '("pline") coords '("c")))
(setq currobj (ssadd (entlast) currobj))
(setq coords (list 
(list 4159.4375 113.7984) 
(list 4085.415 113.9484) 
(list 4085.415 113.7714) 
(list 4159.4375 113.7214)))
(apply 'command (append '("pline") coords '("c")))
(setq currobj (ssadd (entlast) currobj))
(setq coords (list 
(list 4159.4375 113.5784) 
(list 4085.415 113.6284) 
(list 4085.415 113.4514) 
(list 4159.4375 113.5014)))
(apply 'command (append '("pline") coords '("c")))
(setq currobj (ssadd (entlast) currobj))
(setq coords (list 
(list 4159.4375 113.3584) 
(list 4085.415 113.3084) 
(list 4085.415 113.1314) 
(list 4159.4375 113.2814)))
(apply 'command (append '("pline") coords '("c")))
(setq currobj (ssadd (entlast) currobj))
(setq coords (list 
(list 4159.4375 113.1384) 
(list 4085.415 112.9884) 
(list 4085.415 112.8114) 
(list 4159.4375 113.0614)))
(apply 'command (append '("pline") coords '("c")))
(setq currobj (ssadd (entlast) currobj))
(setq coords (list 
(list 4159.4375 112.9184) 
(list 4085.415 112.6684) 
(list 4085.415 112.4914) 
(list 4159.4375 112.8414)))
(apply 'command (append '("pline") coords '("c")))
(setq currobj (ssadd (entlast) currobj))
(setq coords (list 
(list 4159.4375 112.6984) 
(list 4085.415 112.3484) 
(list 4085.415 112.1714) 
(list 4159.4375 112.6214)))
(apply 'command (append '("pline") coords '("c")))
(setq currobj (ssadd (entlast) currobj))
(setq coords (list 
(list 4159.4375 112.4784) 
(list 4085.415 112.0284) 
(list 4085.415 111.8514) 
(list 4159.4375 112.4014)))
(apply 'command (append '("pline") coords '("c")))
(setq currobj (ssadd (entlast) currobj))
(setq coords (list 
(list 4159.4375 112.2584) 
(list 4085.415 111.7084) 
(list 4085.415 111.5314) 
(list 4159.4375 112.1814)))
(apply 'command (append '("pline") coords '("c")))
(setq currobj (ssadd (entlast) currobj))
(setq coords (list 
(list 4159.4375 112.0384) 
(list 4085.415 111.3884) 
(list 4085.415 111.2114) 
(list 4159.4375 111.9614)))
(apply 'command (append '("pline") coords '("c")))
(setq currobj (ssadd (entlast) currobj))
(command "_layer" "set" "nitride" "")
(command "_layer" "set" "text" "")
(command "_circle" "4159.0625,100.8184" "0.075")
(command "_circle" "4159.0625,101.1184" "0.075")
(command "_circle" "4159.0625,101.4184" "0.075")
(command "_circle" "4159.0625,101.7184" "0.075")
(command "_circle" "4159.0625,102.0184" "0.075")
(command "_circle" "4158.7625,100.8184" "0.075")
(command "_circle" "4158.7625,101.1184" "0.075")
(command "_circle" "4158.7625,101.4184" "0.075")
(command "_circle" "4158.7625,101.7184" "0.075")
(command "_circle" "4158.7625,102.0184" "0.075")
(command "_circle" "4158.4625,100.8184" "0.075")
(command "_circle" "4158.4625,101.1184" "0.075")
(command "_circle" "4158.4625,101.4184" "0.075")
(command "_circle" "4158.4625,101.7184" "0.075")
(command "_circle" "4158.4625,102.0184" "0.075")
(command "_circle" "4158.1625,100.8184" "0.075")
(command "_circle" "4158.1625,101.1184" "0.075")
(command "_circle" "4158.1625,101.4184" "0.075")
(command "_circle" "4158.1625,101.7184" "0.075")
(command "_circle" "4158.1625,102.0184" "0.075")
(command "_circle" "4157.8625,100.8184" "0.075")
(command "_circle" "4157.8625,101.1184" "0.075")
(command "_circle" "4157.8625,101.4184" "0.075")
(command "_circle" "4157.8625,101.7184" "0.075")
(command "_circle" "4157.8625,102.0184" "0.075")
(command "_layer" "set" "nitride" "")
(setq coords (list 
(list 4160.2625 126.2614) 
(list 4160.2625 241.9061) 
(list 4159.7375 241.9061) 
(list 4159.7375 126.2614)))
(apply 'command (append '("pline") coords '("c")))
(setq currobj (ssadd (entlast) currobj))
(command "_layer" "set" "prebias" "")
(command "_rectangle" "4159.7375,126.2614" "4160.2625,241.9061")
(setq currobj (ssadd (entlast) currobj))
(command "_layer" "set" "nitride" "")
(setq coords (list 
(list 4160.2625 241.9061) 
(list 4160.5625 251.9061) 
(list 4160.5625 251.9061) 
(list 4160.5625 252.9061) 
(list 4234.585 252.1561) 
(list 4234.585 257.0991) 
(list 4160.5625 256.3491) 
(list 4160.5625 257.3491) 
(list 4160.5625 257.3491) 
(list 4160.2625 267.3491) 
(list 4159.7375 267.3491) 
(list 4159.4375 257.3491) 
(list 4159.4375 257.3491) 
(list 4159.4375 256.3491) 
(list 4085.415 257.0991) 
(list 4085.415 252.1561) 
(list 4159.4375 252.9061) 
(list 4159.4375 251.9061) 
(list 4159.4375 251.9061) 
(list 4159.7375 241.9061)))
(apply 'command (append '("pline") coords '("c")))
(setq currobj (ssadd (entlast) currobj))
(command "_layer" "set" "prebias" "")
(setq coords (list 
(list 4159.4375 241.9061) 
(list 4159.4375 252.9061) 
(list 4085.415 252.1561) 
(list 4085.415 257.0991) 
(list 4159.4375 256.3491) 
(list 4159.4375 267.3491) 
(list 4160.5625 267.3491) 
(list 4160.5625 256.3491) 
(list 4234.585 257.0991) 
(list 4234.585 252.1561) 
(list 4160.5625 252.9061) 
(list 4160.5625 241.9061)))
(apply 'command (append '("pline") coords '("c")))
(setq currobj (ssadd (entlast) currobj))
(command "_layer" "set" "nitride" "")
(command "_layer" "set" "fda1" "")
(setq coords (list 
(list 4160.5625 253.0491) 
(list 4234.585 252.2991) 
(list 4234.585 252.4761) 
(list 4160.5625 253.1261)))
(apply 'command (append '("pline") coords '("c")))
(setq currobj (ssadd (entlast) currobj))
(setq coords (list 
(list 4160.5625 253.2691) 
(list 4234.585 252.6191) 
(list 4234.585 252.7961) 
(list 4160.5625 253.3461)))
(apply 'command (append '("pline") coords '("c")))
(setq currobj (ssadd (entlast) currobj))
(setq coords (list 
(list 4160.5625 253.4891) 
(list 4234.585 252.9391) 
(list 4234.585 253.1161) 
(list 4160.5625 253.5661)))
(apply 'command (append '("pline") coords '("c")))
(setq currobj (ssadd (entlast) currobj))
(setq coords (list 
(list 4160.5625 253.7091) 
(list 4234.585 253.2591) 
(list 4234.585 253.4361) 
(list 4160.5625 253.7861)))
(apply 'command (append '("pline") coords '("c")))
(setq currobj (ssadd (entlast) currobj))
(setq coords (list 
(list 4160.5625 253.9291) 
(list 4234.585 253.5791) 
(list 4234.585 253.7561) 
(list 4160.5625 254.0061)))
(apply 'command (append '("pline") coords '("c")))
(setq currobj (ssadd (entlast) currobj))
(setq coords (list 
(list 4160.5625 254.1491) 
(list 4234.585 253.8991) 
(list 4234.585 254.0761) 
(list 4160.5625 254.2261)))
(apply 'command (append '("pline") coords '("c")))
(setq currobj (ssadd (entlast) currobj))
(setq coords (list 
(list 4160.5625 254.3691) 
(list 4234.585 254.2191) 
(list 4234.585 254.3961) 
(list 4160.5625 254.4461)))
(apply 'command (append '("pline") coords '("c")))
(setq currobj (ssadd (entlast) currobj))
(setq coords (list 
(list 4160.5625 254.5891) 
(list 4234.585 254.5391) 
(list 4234.585 254.7161) 
(list 4160.5625 254.6661)))
(apply 'command (append '("pline") coords '("c")))
(setq currobj (ssadd (entlast) currobj))
(setq coords (list 
(list 4160.5625 254.8091) 
(list 4234.585 254.8591) 
(list 4234.585 255.0361) 
(list 4160.5625 254.8861)))
(apply 'command (append '("pline") coords '("c")))
(setq currobj (ssadd (entlast) currobj))
(setq coords (list 
(list 4160.5625 255.0291) 
(list 4234.585 255.1791) 
(list 4234.585 255.3561) 
(list 4160.5625 255.1061)))
(apply 'command (append '("pline") coords '("c")))
(setq currobj (ssadd (entlast) currobj))
(setq coords (list 
(list 4160.5625 255.2491) 
(list 4234.585 255.4991) 
(list 4234.585 255.6761) 
(list 4160.5625 255.3261)))
(apply 'command (append '("pline") coords '("c")))
(setq currobj (ssadd (entlast) currobj))
(setq coords (list 
(list 4160.5625 255.4691) 
(list 4234.585 255.8191) 
(list 4234.585 255.9961) 
(list 4160.5625 255.5461)))
(apply 'command (append '("pline") coords '("c")))
(setq currobj (ssadd (entlast) currobj))
(setq coords (list 
(list 4160.5625 255.6891) 
(list 4234.585 256.1391) 
(list 4234.585 256.3161) 
(list 4160.5625 255.7661)))
(apply 'command (append '("pline") coords '("c")))
(setq currobj (ssadd (entlast) currobj))
(setq coords (list 
(list 4160.5625 255.9091) 
(list 4234.585 256.4591) 
(list 4234.585 256.6361) 
(list 4160.5625 255.9861)))
(apply 'command (append '("pline") coords '("c")))
(setq currobj (ssadd (entlast) currobj))
(setq coords (list 
(list 4160.5625 256.1291) 
(list 4234.585 256.7791) 
(list 4234.585 256.9561) 
(list 4160.5625 256.2061)))
(apply 'command (append '("pline") coords '("c")))
(setq currobj (ssadd (entlast) currobj))
(setq coords (list 
(list 4159.4375 256.2061) 
(list 4085.415 256.9561) 
(list 4085.415 256.7791) 
(list 4159.4375 256.1291)))
(apply 'command (append '("pline") coords '("c")))
(setq currobj (ssadd (entlast) currobj))
(setq coords (list 
(list 4159.4375 255.9861) 
(list 4085.415 256.6361) 
(list 4085.415 256.4591) 
(list 4159.4375 255.9091)))
(apply 'command (append '("pline") coords '("c")))
(setq currobj (ssadd (entlast) currobj))
(setq coords (list 
(list 4159.4375 255.7661) 
(list 4085.415 256.3161) 
(list 4085.415 256.1391) 
(list 4159.4375 255.6891)))
(apply 'command (append '("pline") coords '("c")))
(setq currobj (ssadd (entlast) currobj))
(setq coords (list 
(list 4159.4375 255.5461) 
(list 4085.415 255.9961) 
(list 4085.415 255.8191) 
(list 4159.4375 255.4691)))
(apply 'command (append '("pline") coords '("c")))
(setq currobj (ssadd (entlast) currobj))
(setq coords (list 
(list 4159.4375 255.3261) 
(list 4085.415 255.6761) 
(list 4085.415 255.4991) 
(list 4159.4375 255.2491)))
(apply 'command (append '("pline") coords '("c")))
(setq currobj (ssadd (entlast) currobj))
(setq coords (list 
(list 4159.4375 255.1061) 
(list 4085.415 255.3561) 
(list 4085.415 255.1791) 
(list 4159.4375 255.0291)))
(apply 'command (append '("pline") coords '("c")))
(setq currobj (ssadd (entlast) currobj))
(setq coords (list 
(list 4159.4375 254.8861) 
(list 4085.415 255.0361) 
(list 4085.415 254.8591) 
(list 4159.4375 254.8091)))
(apply 'command (append '("pline") coords '("c")))
(setq currobj (ssadd (entlast) currobj))
(setq coords (list 
(list 4159.4375 254.6661) 
(list 4085.415 254.7161) 
(list 4085.415 254.5391) 
(list 4159.4375 254.5891)))
(apply 'command (append '("pline") coords '("c")))
(setq currobj (ssadd (entlast) currobj))
(setq coords (list 
(list 4159.4375 254.4461) 
(list 4085.415 254.3961) 
(list 4085.415 254.2191) 
(list 4159.4375 254.3691)))
(apply 'command (append '("pline") coords '("c")))
(setq currobj (ssadd (entlast) currobj))
(setq coords (list 
(list 4159.4375 254.2261) 
(list 4085.415 254.0761) 
(list 4085.415 253.8991) 
(list 4159.4375 254.1491)))
(apply 'command (append '("pline") coords '("c")))
(setq currobj (ssadd (entlast) currobj))
(setq coords (list 
(list 4159.4375 254.0061) 
(list 4085.415 253.7561) 
(list 4085.415 253.5791) 
(list 4159.4375 253.9291)))
(apply 'command (append '("pline") coords '("c")))
(setq currobj (ssadd (entlast) currobj))
(setq coords (list 
(list 4159.4375 253.7861) 
(list 4085.415 253.4361) 
(list 4085.415 253.2591) 
(list 4159.4375 253.7091)))
(apply 'command (append '("pline") coords '("c")))
(setq currobj (ssadd (entlast) currobj))
(setq coords (list 
(list 4159.4375 253.5661) 
(list 4085.415 253.1161) 
(list 4085.415 252.9391) 
(list 4159.4375 253.4891)))
(apply 'command (append '("pline") coords '("c")))
(setq currobj (ssadd (entlast) currobj))
(setq coords (list 
(list 4159.4375 253.3461) 
(list 4085.415 252.7961) 
(list 4085.415 252.6191) 
(list 4159.4375 253.2691)))
(apply 'command (append '("pline") coords '("c")))
(setq currobj (ssadd (entlast) currobj))
(setq coords (list 
(list 4159.4375 253.1261) 
(list 4085.415 252.4761) 
(list 4085.415 252.2991) 
(list 4159.4375 253.0491)))
(apply 'command (append '("pline") coords '("c")))
(setq currobj (ssadd (entlast) currobj))
(command "_layer" "set" "nitride" "")
(command "_layer" "set" "text" "")
(command "_circle" "4159.0625,241.9061" "0.075")
(command "_circle" "4159.0625,242.2061" "0.075")
(command "_circle" "4159.0625,242.5061" "0.075")
(command "_circle" "4159.0625,242.8061" "0.075")
(command "_circle" "4159.0625,243.1061" "0.075")
(command "_circle" "4158.7625,241.9061" "0.075")
(command "_circle" "4158.7625,242.2061" "0.075")
(command "_circle" "4158.7625,242.5061" "0.075")
(command "_circle" "4158.7625,242.8061" "0.075")
(command "_circle" "4158.7625,243.1061" "0.075")
(command "_circle" "4158.4625,241.9061" "0.075")
(command "_circle" "4158.4625,242.2061" "0.075")
(command "_circle" "4158.4625,242.5061" "0.075")
(command "_circle" "4158.4625,242.8061" "0.075")
(command "_circle" "4158.4625,243.1061" "0.075")
(command "_circle" "4158.1625,241.9061" "0.075")
(command "_circle" "4158.1625,242.2061" "0.075")
(command "_circle" "4158.1625,242.5061" "0.075")
(command "_circle" "4158.1625,242.8061" "0.075")
(command "_circle" "4158.1625,243.1061" "0.075")
(command "_circle" "4157.8625,241.9061" "0.075")
(command "_circle" "4157.8625,242.2061" "0.075")
(command "_circle" "4157.8625,242.5061" "0.075")
(command "_circle" "4157.8625,242.8061" "0.075")
(command "_circle" "4157.8625,243.1061" "0.075")
(command "_layer" "set" "nitride" "")
(setq coords (list 
(list 4160.2625 267.3491) 
(list 4160.2625 382.9939) 
(list 4159.7375 382.9939) 
(list 4159.7375 267.3491)))
(apply 'command (append '("pline") coords '("c")))
(setq currobj (ssadd (entlast) currobj))
(command "_layer" "set" "prebias" "")
(command "_rectangle" "4159.7375,267.3491" "4160.2625,382.9939")
(setq currobj (ssadd (entlast) currobj))
(command "_layer" "set" "nitride" "")
(setq coords (list 
(list 4160.2625 382.9939) 
(list 4160.5625 392.9939) 
(list 4160.5625 392.9939) 
(list 4160.5625 393.9939) 
(list 4234.585 393.2439) 
(list 4234.585 398.1869) 
(list 4160.5625 397.4369) 
(list 4160.5625 398.4369) 
(list 4160.5625 398.4369) 
(list 4160.2625 408.4369) 
(list 4159.7375 408.4369) 
(list 4159.4375 398.4369) 
(list 4159.4375 398.4369) 
(list 4159.4375 397.4369) 
(list 4085.415 398.1869) 
(list 4085.415 393.2439) 
(list 4159.4375 393.9939) 
(list 4159.4375 392.9939) 
(list 4159.4375 392.9939) 
(list 4159.7375 382.9939)))
(apply 'command (append '("pline") coords '("c")))
(setq currobj (ssadd (entlast) currobj))
(command "_layer" "set" "prebias" "")
(setq coords (list 
(list 4159.4375 382.9939) 
(list 4159.4375 393.9939) 
(list 4085.415 393.2439) 
(list 4085.415 398.1869) 
(list 4159.4375 397.4369) 
(list 4159.4375 408.4369) 
(list 4160.5625 408.4369) 
(list 4160.5625 397.4369) 
(list 4234.585 398.1869) 
(list 4234.585 393.2439) 
(list 4160.5625 393.9939) 
(list 4160.5625 382.9939)))
(apply 'command (append '("pline") coords '("c")))
(setq currobj (ssadd (entlast) currobj))
(command "_layer" "set" "nitride" "")
(command "_layer" "set" "fda1" "")
(setq coords (list 
(list 4160.5625 394.1369) 
(list 4234.585 393.3869) 
(list 4234.585 393.5639) 
(list 4160.5625 394.2139)))
(apply 'command (append '("pline") coords '("c")))
(setq currobj (ssadd (entlast) currobj))
(setq coords (list 
(list 4160.5625 394.3569) 
(list 4234.585 393.7069) 
(list 4234.585 393.8839) 
(list 4160.5625 394.4339)))
(apply 'command (append '("pline") coords '("c")))
(setq currobj (ssadd (entlast) currobj))
(setq coords (list 
(list 4160.5625 394.5769) 
(list 4234.585 394.0269) 
(list 4234.585 394.2039) 
(list 4160.5625 394.6539)))
(apply 'command (append '("pline") coords '("c")))
(setq currobj (ssadd (entlast) currobj))
(setq coords (list 
(list 4160.5625 394.7969) 
(list 4234.585 394.3469) 
(list 4234.585 394.5239) 
(list 4160.5625 394.8739)))
(apply 'command (append '("pline") coords '("c")))
(setq currobj (ssadd (entlast) currobj))
(setq coords (list 
(list 4160.5625 395.0169) 
(list 4234.585 394.6669) 
(list 4234.585 394.8439) 
(list 4160.5625 395.0939)))
(apply 'command (append '("pline") coords '("c")))
(setq currobj (ssadd (entlast) currobj))
(setq coords (list 
(list 4160.5625 395.2369) 
(list 4234.585 394.9869) 
(list 4234.585 395.1639) 
(list 4160.5625 395.3139)))
(apply 'command (append '("pline") coords '("c")))
(setq currobj (ssadd (entlast) currobj))
(setq coords (list 
(list 4160.5625 395.4569) 
(list 4234.585 395.3069) 
(list 4234.585 395.4839) 
(list 4160.5625 395.5339)))
(apply 'command (append '("pline") coords '("c")))
(setq currobj (ssadd (entlast) currobj))
(setq coords (list 
(list 4160.5625 395.6769) 
(list 4234.585 395.6269) 
(list 4234.585 395.8039) 
(list 4160.5625 395.7539)))
(apply 'command (append '("pline") coords '("c")))
(setq currobj (ssadd (entlast) currobj))
(setq coords (list 
(list 4160.5625 395.8969) 
(list 4234.585 395.9469) 
(list 4234.585 396.1239) 
(list 4160.5625 395.9739)))
(apply 'command (append '("pline") coords '("c")))
(setq currobj (ssadd (entlast) currobj))
(setq coords (list 
(list 4160.5625 396.1169) 
(list 4234.585 396.2669) 
(list 4234.585 396.4439) 
(list 4160.5625 396.1939)))
(apply 'command (append '("pline") coords '("c")))
(setq currobj (ssadd (entlast) currobj))
(setq coords (list 
(list 4160.5625 396.3369) 
(list 4234.585 396.5869) 
(list 4234.585 396.7639) 
(list 4160.5625 396.4139)))
(apply 'command (append '("pline") coords '("c")))
(setq currobj (ssadd (entlast) currobj))
(setq coords (list 
(list 4160.5625 396.5569) 
(list 4234.585 396.9069) 
(list 4234.585 397.0839) 
(list 4160.5625 396.6339)))
(apply 'command (append '("pline") coords '("c")))
(setq currobj (ssadd (entlast) currobj))
(setq coords (list 
(list 4160.5625 396.7769) 
(list 4234.585 397.2269) 
(list 4234.585 397.4039) 
(list 4160.5625 396.8539)))
(apply 'command (append '("pline") coords '("c")))
(setq currobj (ssadd (entlast) currobj))
(setq coords (list 
(list 4160.5625 396.9969) 
(list 4234.585 397.5469) 
(list 4234.585 397.7239) 
(list 4160.5625 397.0739)))
(apply 'command (append '("pline") coords '("c")))
(setq currobj (ssadd (entlast) currobj))
(setq coords (list 
(list 4160.5625 397.2169) 
(list 4234.585 397.8669) 
(list 4234.585 398.0439) 
(list 4160.5625 397.2939)))
(apply 'command (append '("pline") coords '("c")))
(setq currobj (ssadd (entlast) currobj))
(setq coords (list 
(list 4159.4375 397.2939) 
(list 4085.415 398.0439) 
(list 4085.415 397.8669) 
(list 4159.4375 397.2169)))
(apply 'command (append '("pline") coords '("c")))
(setq currobj (ssadd (entlast) currobj))
(setq coords (list 
(list 4159.4375 397.0739) 
(list 4085.415 397.7239) 
(list 4085.415 397.5469) 
(list 4159.4375 396.9969)))
(apply 'command (append '("pline") coords '("c")))
(setq currobj (ssadd (entlast) currobj))
(setq coords (list 
(list 4159.4375 396.8539) 
(list 4085.415 397.4039) 
(list 4085.415 397.2269) 
(list 4159.4375 396.7769)))
(apply 'command (append '("pline") coords '("c")))
(setq currobj (ssadd (entlast) currobj))
(setq coords (list 
(list 4159.4375 396.6339) 
(list 4085.415 397.0839) 
(list 4085.415 396.9069) 
(list 4159.4375 396.5569)))
(apply 'command (append '("pline") coords '("c")))
(setq currobj (ssadd (entlast) currobj))
(setq coords (list 
(list 4159.4375 396.4139) 
(list 4085.415 396.7639) 
(list 4085.415 396.5869) 
(list 4159.4375 396.3369)))
(apply 'command (append '("pline") coords '("c")))
(setq currobj (ssadd (entlast) currobj))
(setq coords (list 
(list 4159.4375 396.1939) 
(list 4085.415 396.4439) 
(list 4085.415 396.2669) 
(list 4159.4375 396.1169)))
(apply 'command (append '("pline") coords '("c")))
(setq currobj (ssadd (entlast) currobj))
(setq coords (list 
(list 4159.4375 395.9739) 
(list 4085.415 396.1239) 
(list 4085.415 395.9469) 
(list 4159.4375 395.8969)))
(apply 'command (append '("pline") coords '("c")))
(setq currobj (ssadd (entlast) currobj))
(setq coords (list 
(list 4159.4375 395.7539) 
(list 4085.415 395.8039) 
(list 4085.415 395.6269) 
(list 4159.4375 395.6769)))
(apply 'command (append '("pline") coords '("c")))
(setq currobj (ssadd (entlast) currobj))
(setq coords (list 
(list 4159.4375 395.5339) 
(list 4085.415 395.4839) 
(list 4085.415 395.3069) 
(list 4159.4375 395.4569)))
(apply 'command (append '("pline") coords '("c")))
(setq currobj (ssadd (entlast) currobj))
(setq coords (list 
(list 4159.4375 395.3139) 
(list 4085.415 395.1639) 
(list 4085.415 394.9869) 
(list 4159.4375 395.2369)))
(apply 'command (append '("pline") coords '("c")))
(setq currobj (ssadd (entlast) currobj))
(setq coords (list 
(list 4159.4375 395.0939) 
(list 4085.415 394.8439) 
(list 4085.415 394.6669) 
(list 4159.4375 395.0169)))
(apply 'command (append '("pline") coords '("c")))
(setq currobj (ssadd (entlast) currobj))
(setq coords (list 
(list 4159.4375 394.8739) 
(list 4085.415 394.5239) 
(list 4085.415 394.3469) 
(list 4159.4375 394.7969)))
(apply 'command (append '("pline") coords '("c")))
(setq currobj (ssadd (entlast) currobj))
(setq coords (list 
(list 4159.4375 394.6539) 
(list 4085.415 394.2039) 
(list 4085.415 394.0269) 
(list 4159.4375 394.5769)))
(apply 'command (append '("pline") coords '("c")))
(setq currobj (ssadd (entlast) currobj))
(setq coords (list 
(list 4159.4375 394.4339) 
(list 4085.415 393.8839) 
(list 4085.415 393.7069) 
(list 4159.4375 394.3569)))
(apply 'command (append '("pline") coords '("c")))
(setq currobj (ssadd (entlast) currobj))
(setq coords (list 
(list 4159.4375 394.2139) 
(list 4085.415 393.5639) 
(list 4085.415 393.3869) 
(list 4159.4375 394.1369)))
(apply 'command (append '("pline") coords '("c")))
(setq currobj (ssadd (entlast) currobj))
(command "_layer" "set" "nitride" "")
(command "_layer" "set" "text" "")
(command "_circle" "4159.0625,382.9939" "0.075")
(command "_circle" "4159.0625,383.2939" "0.075")
(command "_circle" "4159.0625,383.5939" "0.075")
(command "_circle" "4159.0625,383.8939" "0.075")
(command "_circle" "4159.0625,384.1939" "0.075")
(command "_circle" "4158.7625,382.9939" "0.075")
(command "_circle" "4158.7625,383.2939" "0.075")
(command "_circle" "4158.7625,383.5939" "0.075")
(command "_circle" "4158.7625,383.8939" "0.075")
(command "_circle" "4158.7625,384.1939" "0.075")
(command "_circle" "4158.4625,382.9939" "0.075")
(command "_circle" "4158.4625,383.2939" "0.075")
(command "_circle" "4158.4625,383.5939" "0.075")
(command "_circle" "4158.4625,383.8939" "0.075")
(command "_circle" "4158.4625,384.1939" "0.075")
(command "_circle" "4158.1625,382.9939" "0.075")
(command "_circle" "4158.1625,383.2939" "0.075")
(command "_circle" "4158.1625,383.5939" "0.075")
(command "_circle" "4158.1625,383.8939" "0.075")
(command "_circle" "4158.1625,384.1939" "0.075")
(command "_circle" "4157.8625,382.9939" "0.075")
(command "_circle" "4157.8625,383.2939" "0.075")
(command "_circle" "4157.8625,383.5939" "0.075")
(command "_circle" "4157.8625,383.8939" "0.075")
(command "_circle" "4157.8625,384.1939" "0.075")
(command "_layer" "set" "nitride" "")
(setq coords (list 
(list 4160.2625 408.4369) 
(list 4160.2625 524.0816) 
(list 4159.7375 524.0816) 
(list 4159.7375 408.4369)))
(apply 'command (append '("pline") coords '("c")))
(setq currobj (ssadd (entlast) currobj))
(command "_layer" "set" "prebias" "")
(command "_rectangle" "4159.7375,408.4369" "4160.2625,524.0816")
(setq currobj (ssadd (entlast) currobj))
(command "_layer" "set" "nitride" "")
(setq coords (list 
(list 4160.2625 524.0816) 
(list 4160.5625 534.0816) 
(list 4160.5625 534.0816) 
(list 4160.5625 535.0816) 
(list 4234.585 534.3316) 
(list 4234.585 539.2746) 
(list 4160.5625 538.5246) 
(list 4160.5625 539.5246) 
(list 4160.5625 539.5246) 
(list 4160.2625 549.5246) 
(list 4159.7375 549.5246) 
(list 4159.4375 539.5246) 
(list 4159.4375 539.5246) 
(list 4159.4375 538.5246) 
(list 4085.415 539.2746) 
(list 4085.415 534.3316) 
(list 4159.4375 535.0816) 
(list 4159.4375 534.0816) 
(list 4159.4375 534.0816) 
(list 4159.7375 524.0816)))
(apply 'command (append '("pline") coords '("c")))
(setq currobj (ssadd (entlast) currobj))
(command "_layer" "set" "prebias" "")
(setq coords (list 
(list 4159.4375 524.0816) 
(list 4159.4375 535.0816) 
(list 4085.415 534.3316) 
(list 4085.415 539.2746) 
(list 4159.4375 538.5246) 
(list 4159.4375 549.5246) 
(list 4160.5625 549.5246) 
(list 4160.5625 538.5246) 
(list 4234.585 539.2746) 
(list 4234.585 534.3316) 
(list 4160.5625 535.0816) 
(list 4160.5625 524.0816)))
(apply 'command (append '("pline") coords '("c")))
(setq currobj (ssadd (entlast) currobj))
(command "_layer" "set" "nitride" "")
(command "_layer" "set" "fda1" "")
(setq coords (list 
(list 4160.5625 535.2246) 
(list 4234.585 534.4746) 
(list 4234.585 534.6516) 
(list 4160.5625 535.3016)))
(apply 'command (append '("pline") coords '("c")))
(setq currobj (ssadd (entlast) currobj))
(setq coords (list 
(list 4160.5625 535.4446) 
(list 4234.585 534.7946) 
(list 4234.585 534.9716) 
(list 4160.5625 535.5216)))
(apply 'command (append '("pline") coords '("c")))
(setq currobj (ssadd (entlast) currobj))
(setq coords (list 
(list 4160.5625 535.6646) 
(list 4234.585 535.1146) 
(list 4234.585 535.2916) 
(list 4160.5625 535.7416)))
(apply 'command (append '("pline") coords '("c")))
(setq currobj (ssadd (entlast) currobj))
(setq coords (list 
(list 4160.5625 535.8846) 
(list 4234.585 535.4346) 
(list 4234.585 535.6116) 
(list 4160.5625 535.9616)))
(apply 'command (append '("pline") coords '("c")))
(setq currobj (ssadd (entlast) currobj))
(setq coords (list 
(list 4160.5625 536.1046) 
(list 4234.585 535.7546) 
(list 4234.585 535.9316) 
(list 4160.5625 536.1816)))
(apply 'command (append '("pline") coords '("c")))
(setq currobj (ssadd (entlast) currobj))
(setq coords (list 
(list 4160.5625 536.3246) 
(list 4234.585 536.0746) 
(list 4234.585 536.2516) 
(list 4160.5625 536.4016)))
(apply 'command (append '("pline") coords '("c")))
(setq currobj (ssadd (entlast) currobj))
(setq coords (list 
(list 4160.5625 536.5446) 
(list 4234.585 536.3946) 
(list 4234.585 536.5716) 
(list 4160.5625 536.6216)))
(apply 'command (append '("pline") coords '("c")))
(setq currobj (ssadd (entlast) currobj))
(setq coords (list 
(list 4160.5625 536.7646) 
(list 4234.585 536.7146) 
(list 4234.585 536.8916) 
(list 4160.5625 536.8416)))
(apply 'command (append '("pline") coords '("c")))
(setq currobj (ssadd (entlast) currobj))
(setq coords (list 
(list 4160.5625 536.9846) 
(list 4234.585 537.0346) 
(list 4234.585 537.2116) 
(list 4160.5625 537.0616)))
(apply 'command (append '("pline") coords '("c")))
(setq currobj (ssadd (entlast) currobj))
(setq coords (list 
(list 4160.5625 537.2046) 
(list 4234.585 537.3546) 
(list 4234.585 537.5316) 
(list 4160.5625 537.2816)))
(apply 'command (append '("pline") coords '("c")))
(setq currobj (ssadd (entlast) currobj))
(setq coords (list 
(list 4160.5625 537.4246) 
(list 4234.585 537.6746) 
(list 4234.585 537.8516) 
(list 4160.5625 537.5016)))
(apply 'command (append '("pline") coords '("c")))
(setq currobj (ssadd (entlast) currobj))
(setq coords (list 
(list 4160.5625 537.6446) 
(list 4234.585 537.9946) 
(list 4234.585 538.1716) 
(list 4160.5625 537.7216)))
(apply 'command (append '("pline") coords '("c")))
(setq currobj (ssadd (entlast) currobj))
(setq coords (list 
(list 4160.5625 537.8646) 
(list 4234.585 538.3146) 
(list 4234.585 538.4916) 
(list 4160.5625 537.9416)))
(apply 'command (append '("pline") coords '("c")))
(setq currobj (ssadd (entlast) currobj))
(setq coords (list 
(list 4160.5625 538.0846) 
(list 4234.585 538.6346) 
(list 4234.585 538.8116) 
(list 4160.5625 538.1616)))
(apply 'command (append '("pline") coords '("c")))
(setq currobj (ssadd (entlast) currobj))
(setq coords (list 
(list 4160.5625 538.3046) 
(list 4234.585 538.9546) 
(list 4234.585 539.1316) 
(list 4160.5625 538.3816)))
(apply 'command (append '("pline") coords '("c")))
(setq currobj (ssadd (entlast) currobj))
(setq coords (list 
(list 4159.4375 538.3816) 
(list 4085.415 539.1316) 
(list 4085.415 538.9546) 
(list 4159.4375 538.3046)))
(apply 'command (append '("pline") coords '("c")))
(setq currobj (ssadd (entlast) currobj))
(setq coords (list 
(list 4159.4375 538.1616) 
(list 4085.415 538.8116) 
(list 4085.415 538.6346) 
(list 4159.4375 538.0846)))
(apply 'command (append '("pline") coords '("c")))
(setq currobj (ssadd (entlast) currobj))
(setq coords (list 
(list 4159.4375 537.9416) 
(list 4085.415 538.4916) 
(list 4085.415 538.3146) 
(list 4159.4375 537.8646)))
(apply 'command (append '("pline") coords '("c")))
(setq currobj (ssadd (entlast) currobj))
(setq coords (list 
(list 4159.4375 537.7216) 
(list 4085.415 538.1716) 
(list 4085.415 537.9946) 
(list 4159.4375 537.6446)))
(apply 'command (append '("pline") coords '("c")))
(setq currobj (ssadd (entlast) currobj))
(setq coords (list 
(list 4159.4375 537.5016) 
(list 4085.415 537.8516) 
(list 4085.415 537.6746) 
(list 4159.4375 537.4246)))
(apply 'command (append '("pline") coords '("c")))
(setq currobj (ssadd (entlast) currobj))
(setq coords (list 
(list 4159.4375 537.2816) 
(list 4085.415 537.5316) 
(list 4085.415 537.3546) 
(list 4159.4375 537.2046)))
(apply 'command (append '("pline") coords '("c")))
(setq currobj (ssadd (entlast) currobj))
(setq coords (list 
(list 4159.4375 537.0616) 
(list 4085.415 537.2116) 
(list 4085.415 537.0346) 
(list 4159.4375 536.9846)))
(apply 'command (append '("pline") coords '("c")))
(setq currobj (ssadd (entlast) currobj))
(setq coords (list 
(list 4159.4375 536.8416) 
(list 4085.415 536.8916) 
(list 4085.415 536.7146) 
(list 4159.4375 536.7646)))
(apply 'command (append '("pline") coords '("c")))
(setq currobj (ssadd (entlast) currobj))
(setq coords (list 
(list 4159.4375 536.6216) 
(list 4085.415 536.5716) 
(list 4085.415 536.3946) 
(list 4159.4375 536.5446)))
(apply 'command (append '("pline") coords '("c")))
(setq currobj (ssadd (entlast) currobj))
(setq coords (list 
(list 4159.4375 536.4016) 
(list 4085.415 536.2516) 
(list 4085.415 536.0746) 
(list 4159.4375 536.3246)))
(apply 'command (append '("pline") coords '("c")))
(setq currobj (ssadd (entlast) currobj))
(setq coords (list 
(list 4159.4375 536.1816) 
(list 4085.415 535.9316) 
(list 4085.415 535.7546) 
(list 4159.4375 536.1046)))
(apply 'command (append '("pline") coords '("c")))
(setq currobj (ssadd (entlast) currobj))
(setq coords (list 
(list 4159.4375 535.9616) 
(list 4085.415 535.6116) 
(list 4085.415 535.4346) 
(list 4159.4375 535.8846)))
(apply 'command (append '("pline") coords '("c")))
(setq currobj (ssadd (entlast) currobj))
(setq coords (list 
(list 4159.4375 535.7416) 
(list 4085.415 535.2916) 
(list 4085.415 535.1146) 
(list 4159.4375 535.6646)))
(apply 'command (append '("pline") coords '("c")))
(setq currobj (ssadd (entlast) currobj))
(setq coords (list 
(list 4159.4375 535.5216) 
(list 4085.415 534.9716) 
(list 4085.415 534.7946) 
(list 4159.4375 535.4446)))
(apply 'command (append '("pline") coords '("c")))
(setq currobj (ssadd (entlast) currobj))
(setq coords (list 
(list 4159.4375 535.3016) 
(list 4085.415 534.6516) 
(list 4085.415 534.4746) 
(list 4159.4375 535.2246)))
(apply 'command (append '("pline") coords '("c")))
(setq currobj (ssadd (entlast) currobj))
(command "_layer" "set" "nitride" "")
(command "_layer" "set" "text" "")
(command "_circle" "4159.0625,524.0816" "0.075")
(command "_circle" "4159.0625,524.3816" "0.075")
(command "_circle" "4159.0625,524.6816" "0.075")
(command "_circle" "4159.0625,524.9816" "0.075")
(command "_circle" "4159.0625,525.2816" "0.075")
(command "_circle" "4158.7625,524.0816" "0.075")
(command "_circle" "4158.7625,524.3816" "0.075")
(command "_circle" "4158.7625,524.6816" "0.075")
(command "_circle" "4158.7625,524.9816" "0.075")
(command "_circle" "4158.7625,525.2816" "0.075")
(command "_circle" "4158.4625,524.0816" "0.075")
(command "_circle" "4158.4625,524.3816" "0.075")
(command "_circle" "4158.4625,524.6816" "0.075")
(command "_circle" "4158.4625,524.9816" "0.075")
(command "_circle" "4158.4625,525.2816" "0.075")
(command "_circle" "4158.1625,524.0816" "0.075")
(command "_circle" "4158.1625,524.3816" "0.075")
(command "_circle" "4158.1625,524.6816" "0.075")
(command "_circle" "4158.1625,524.9816" "0.075")
(command "_circle" "4158.1625,525.2816" "0.075")
(command "_circle" "4157.8625,524.0816" "0.075")
(command "_circle" "4157.8625,524.3816" "0.075")
(command "_circle" "4157.8625,524.6816" "0.075")
(command "_circle" "4157.8625,524.9816" "0.075")
(command "_circle" "4157.8625,525.2816" "0.075")
(command "_layer" "set" "nitride" "")
(setq coords (list 
(list 4160.2625 549.5246) 
(list 4160.2625 665.1693) 
(list 4159.7375 665.1693) 
(list 4159.7375 549.5246)))
(apply 'command (append '("pline") coords '("c")))
(setq currobj (ssadd (entlast) currobj))
(command "_layer" "set" "prebias" "")
(command "_rectangle" "4159.7375,549.5246" "4160.2625,665.1693")
(setq currobj (ssadd (entlast) currobj))
(command "_layer" "set" "nitride" "")
(setq coords (list 
(list 4160.2625 665.1693) 
(list 4160.5625 675.1693) 
(list 4160.5625 675.1693) 
(list 4160.5625 676.1693) 
(list 4234.585 675.4193) 
(list 4234.585 680.3623) 
(list 4160.5625 679.6123) 
(list 4160.5625 680.6123) 
(list 4160.5625 680.6123) 
(list 4160.2625 690.6123) 
(list 4159.7375 690.6123) 
(list 4159.4375 680.6123) 
(list 4159.4375 680.6123) 
(list 4159.4375 679.6123) 
(list 4085.415 680.3623) 
(list 4085.415 675.4193) 
(list 4159.4375 676.1693) 
(list 4159.4375 675.1693) 
(list 4159.4375 675.1693) 
(list 4159.7375 665.1693)))
(apply 'command (append '("pline") coords '("c")))
(setq currobj (ssadd (entlast) currobj))
(command "_layer" "set" "prebias" "")
(setq coords (list 
(list 4159.4375 665.1693) 
(list 4159.4375 676.1693) 
(list 4085.415 675.4193) 
(list 4085.415 680.3623) 
(list 4159.4375 679.6123) 
(list 4159.4375 690.6123) 
(list 4160.5625 690.6123) 
(list 4160.5625 679.6123) 
(list 4234.585 680.3623) 
(list 4234.585 675.4193) 
(list 4160.5625 676.1693) 
(list 4160.5625 665.1693)))
(apply 'command (append '("pline") coords '("c")))
(setq currobj (ssadd (entlast) currobj))
(command "_layer" "set" "nitride" "")
(command "_layer" "set" "fda1" "")
(setq coords (list 
(list 4160.5625 676.3123) 
(list 4234.585 675.5623) 
(list 4234.585 675.7393) 
(list 4160.5625 676.3893)))
(apply 'command (append '("pline") coords '("c")))
(setq currobj (ssadd (entlast) currobj))
(setq coords (list 
(list 4160.5625 676.5323) 
(list 4234.585 675.8823) 
(list 4234.585 676.0593) 
(list 4160.5625 676.6093)))
(apply 'command (append '("pline") coords '("c")))
(setq currobj (ssadd (entlast) currobj))
(setq coords (list 
(list 4160.5625 676.7523) 
(list 4234.585 676.2023) 
(list 4234.585 676.3793) 
(list 4160.5625 676.8293)))
(apply 'command (append '("pline") coords '("c")))
(setq currobj (ssadd (entlast) currobj))
(setq coords (list 
(list 4160.5625 676.9723) 
(list 4234.585 676.5223) 
(list 4234.585 676.6993) 
(list 4160.5625 677.0493)))
(apply 'command (append '("pline") coords '("c")))
(setq currobj (ssadd (entlast) currobj))
(setq coords (list 
(list 4160.5625 677.1923) 
(list 4234.585 676.8423) 
(list 4234.585 677.0193) 
(list 4160.5625 677.2693)))
(apply 'command (append '("pline") coords '("c")))
(setq currobj (ssadd (entlast) currobj))
(setq coords (list 
(list 4160.5625 677.4123) 
(list 4234.585 677.1623) 
(list 4234.585 677.3393) 
(list 4160.5625 677.4893)))
(apply 'command (append '("pline") coords '("c")))
(setq currobj (ssadd (entlast) currobj))
(setq coords (list 
(list 4160.5625 677.6323) 
(list 4234.585 677.4823) 
(list 4234.585 677.6593) 
(list 4160.5625 677.7093)))
(apply 'command (append '("pline") coords '("c")))
(setq currobj (ssadd (entlast) currobj))
(setq coords (list 
(list 4160.5625 677.8523) 
(list 4234.585 677.8023) 
(list 4234.585 677.9793) 
(list 4160.5625 677.9293)))
(apply 'command (append '("pline") coords '("c")))
(setq currobj (ssadd (entlast) currobj))
(setq coords (list 
(list 4160.5625 678.0723) 
(list 4234.585 678.1223) 
(list 4234.585 678.2993) 
(list 4160.5625 678.1493)))
(apply 'command (append '("pline") coords '("c")))
(setq currobj (ssadd (entlast) currobj))
(setq coords (list 
(list 4160.5625 678.2923) 
(list 4234.585 678.4423) 
(list 4234.585 678.6193) 
(list 4160.5625 678.3693)))
(apply 'command (append '("pline") coords '("c")))
(setq currobj (ssadd (entlast) currobj))
(setq coords (list 
(list 4160.5625 678.5123) 
(list 4234.585 678.7623) 
(list 4234.585 678.9393) 
(list 4160.5625 678.5893)))
(apply 'command (append '("pline") coords '("c")))
(setq currobj (ssadd (entlast) currobj))
(setq coords (list 
(list 4160.5625 678.7323) 
(list 4234.585 679.0823) 
(list 4234.585 679.2593) 
(list 4160.5625 678.8093)))
(apply 'command (append '("pline") coords '("c")))
(setq currobj (ssadd (entlast) currobj))
(setq coords (list 
(list 4160.5625 678.9523) 
(list 4234.585 679.4023) 
(list 4234.585 679.5793) 
(list 4160.5625 679.0293)))
(apply 'command (append '("pline") coords '("c")))
(setq currobj (ssadd (entlast) currobj))
(setq coords (list 
(list 4160.5625 679.1723) 
(list 4234.585 679.7223) 
(list 4234.585 679.8993) 
(list 4160.5625 679.2493)))
(apply 'command (append '("pline") coords '("c")))
(setq currobj (ssadd (entlast) currobj))
(setq coords (list 
(list 4160.5625 679.3923) 
(list 4234.585 680.0423) 
(list 4234.585 680.2193) 
(list 4160.5625 679.4693)))
(apply 'command (append '("pline") coords '("c")))
(setq currobj (ssadd (entlast) currobj))
(setq coords (list 
(list 4159.4375 679.4693) 
(list 4085.415 680.2193) 
(list 4085.415 680.0423) 
(list 4159.4375 679.3923)))
(apply 'command (append '("pline") coords '("c")))
(setq currobj (ssadd (entlast) currobj))
(setq coords (list 
(list 4159.4375 679.2493) 
(list 4085.415 679.8993) 
(list 4085.415 679.7223) 
(list 4159.4375 679.1723)))
(apply 'command (append '("pline") coords '("c")))
(setq currobj (ssadd (entlast) currobj))
(setq coords (list 
(list 4159.4375 679.0293) 
(list 4085.415 679.5793) 
(list 4085.415 679.4023) 
(list 4159.4375 678.9523)))
(apply 'command (append '("pline") coords '("c")))
(setq currobj (ssadd (entlast) currobj))
(setq coords (list 
(list 4159.4375 678.8093) 
(list 4085.415 679.2593) 
(list 4085.415 679.0823) 
(list 4159.4375 678.7323)))
(apply 'command (append '("pline") coords '("c")))
(setq currobj (ssadd (entlast) currobj))
(setq coords (list 
(list 4159.4375 678.5893) 
(list 4085.415 678.9393) 
(list 4085.415 678.7623) 
(list 4159.4375 678.5123)))
(apply 'command (append '("pline") coords '("c")))
(setq currobj (ssadd (entlast) currobj))
(setq coords (list 
(list 4159.4375 678.3693) 
(list 4085.415 678.6193) 
(list 4085.415 678.4423) 
(list 4159.4375 678.2923)))
(apply 'command (append '("pline") coords '("c")))
(setq currobj (ssadd (entlast) currobj))
(setq coords (list 
(list 4159.4375 678.1493) 
(list 4085.415 678.2993) 
(list 4085.415 678.1223) 
(list 4159.4375 678.0723)))
(apply 'command (append '("pline") coords '("c")))
(setq currobj (ssadd (entlast) currobj))
(setq coords (list 
(list 4159.4375 677.9293) 
(list 4085.415 677.9793) 
(list 4085.415 677.8023) 
(list 4159.4375 677.8523)))
(apply 'command (append '("pline") coords '("c")))
(setq currobj (ssadd (entlast) currobj))
(setq coords (list 
(list 4159.4375 677.7093) 
(list 4085.415 677.6593) 
(list 4085.415 677.4823) 
(list 4159.4375 677.6323)))
(apply 'command (append '("pline") coords '("c")))
(setq currobj (ssadd (entlast) currobj))
(setq coords (list 
(list 4159.4375 677.4893) 
(list 4085.415 677.3393) 
(list 4085.415 677.1623) 
(list 4159.4375 677.4123)))
(apply 'command (append '("pline") coords '("c")))
(setq currobj (ssadd (entlast) currobj))
(setq coords (list 
(list 4159.4375 677.2693) 
(list 4085.415 677.0193) 
(list 4085.415 676.8423) 
(list 4159.4375 677.1923)))
(apply 'command (append '("pline") coords '("c")))
(setq currobj (ssadd (entlast) currobj))
(setq coords (list 
(list 4159.4375 677.0493) 
(list 4085.415 676.6993) 
(list 4085.415 676.5223) 
(list 4159.4375 676.9723)))
(apply 'command (append '("pline") coords '("c")))
(setq currobj (ssadd (entlast) currobj))
(setq coords (list 
(list 4159.4375 676.8293) 
(list 4085.415 676.3793) 
(list 4085.415 676.2023) 
(list 4159.4375 676.7523)))
(apply 'command (append '("pline") coords '("c")))
(setq currobj (ssadd (entlast) currobj))
(setq coords (list 
(list 4159.4375 676.6093) 
(list 4085.415 676.0593) 
(list 4085.415 675.8823) 
(list 4159.4375 676.5323)))
(apply 'command (append '("pline") coords '("c")))
(setq currobj (ssadd (entlast) currobj))
(setq coords (list 
(list 4159.4375 676.3893) 
(list 4085.415 675.7393) 
(list 4085.415 675.5623) 
(list 4159.4375 676.3123)))
(apply 'command (append '("pline") coords '("c")))
(setq currobj (ssadd (entlast) currobj))
(command "_layer" "set" "nitride" "")
(command "_layer" "set" "text" "")
(command "_circle" "4159.0625,665.1693" "0.075")
(command "_circle" "4159.0625,665.4693" "0.075")
(command "_circle" "4159.0625,665.7693" "0.075")
(command "_circle" "4159.0625,666.0693" "0.075")
(command "_circle" "4159.0625,666.3693" "0.075")
(command "_circle" "4158.7625,665.1693" "0.075")
(command "_circle" "4158.7625,665.4693" "0.075")
(command "_circle" "4158.7625,665.7693" "0.075")
(command "_circle" "4158.7625,666.0693" "0.075")
(command "_circle" "4158.7625,666.3693" "0.075")
(command "_circle" "4158.4625,665.1693" "0.075")
(command "_circle" "4158.4625,665.4693" "0.075")
(command "_circle" "4158.4625,665.7693" "0.075")
(command "_circle" "4158.4625,666.0693" "0.075")
(command "_circle" "4158.4625,666.3693" "0.075")
(command "_circle" "4158.1625,665.1693" "0.075")
(command "_circle" "4158.1625,665.4693" "0.075")
(command "_circle" "4158.1625,665.7693" "0.075")
(command "_circle" "4158.1625,666.0693" "0.075")
(command "_circle" "4158.1625,666.3693" "0.075")
(command "_circle" "4157.8625,665.1693" "0.075")
(command "_circle" "4157.8625,665.4693" "0.075")
(command "_circle" "4157.8625,665.7693" "0.075")
(command "_circle" "4157.8625,666.0693" "0.075")
(command "_circle" "4157.8625,666.3693" "0.075")
(command "_layer" "set" "nitride" "")
(setq coords (list 
(list 4160.2625 690.6123) 
(list 4160.2625 806.257) 
(list 4159.7375 806.257) 
(list 4159.7375 690.6123)))
(apply 'command (append '("pline") coords '("c")))
(setq currobj (ssadd (entlast) currobj))
(command "_layer" "set" "prebias" "")
(command "_rectangle" "4159.7375,690.6123" "4160.2625,806.257")
(setq currobj (ssadd (entlast) currobj))
(command "_layer" "set" "nitride" "")
(setq coords (list 
(list 4160.2625 806.257) 
(list 4160.5625 816.257) 
(list 4160.5625 816.257) 
(list 4160.5625 817.257) 
(list 4234.585 816.507) 
(list 4234.585 821.45) 
(list 4160.5625 820.7) 
(list 4160.5625 821.7) 
(list 4160.5625 821.7) 
(list 4160.2625 831.7) 
(list 4159.7375 831.7) 
(list 4159.4375 821.7) 
(list 4159.4375 821.7) 
(list 4159.4375 820.7) 
(list 4085.415 821.45) 
(list 4085.415 816.507) 
(list 4159.4375 817.257) 
(list 4159.4375 816.257) 
(list 4159.4375 816.257) 
(list 4159.7375 806.257)))
(apply 'command (append '("pline") coords '("c")))
(setq currobj (ssadd (entlast) currobj))
(command "_layer" "set" "prebias" "")
(setq coords (list 
(list 4159.4375 806.257) 
(list 4159.4375 817.257) 
(list 4085.415 816.507) 
(list 4085.415 821.45) 
(list 4159.4375 820.7) 
(list 4159.4375 831.7) 
(list 4160.5625 831.7) 
(list 4160.5625 820.7) 
(list 4234.585 821.45) 
(list 4234.585 816.507) 
(list 4160.5625 817.257) 
(list 4160.5625 806.257)))
(apply 'command (append '("pline") coords '("c")))
(setq currobj (ssadd (entlast) currobj))
(command "_layer" "set" "nitride" "")
(command "_layer" "set" "fda1" "")
(setq coords (list 
(list 4160.5625 817.4) 
(list 4234.585 816.65) 
(list 4234.585 816.827) 
(list 4160.5625 817.477)))
(apply 'command (append '("pline") coords '("c")))
(setq currobj (ssadd (entlast) currobj))
(setq coords (list 
(list 4160.5625 817.62) 
(list 4234.585 816.97) 
(list 4234.585 817.147) 
(list 4160.5625 817.697)))
(apply 'command (append '("pline") coords '("c")))
(setq currobj (ssadd (entlast) currobj))
(setq coords (list 
(list 4160.5625 817.84) 
(list 4234.585 817.29) 
(list 4234.585 817.467) 
(list 4160.5625 817.917)))
(apply 'command (append '("pline") coords '("c")))
(setq currobj (ssadd (entlast) currobj))
(setq coords (list 
(list 4160.5625 818.06) 
(list 4234.585 817.61) 
(list 4234.585 817.787) 
(list 4160.5625 818.137)))
(apply 'command (append '("pline") coords '("c")))
(setq currobj (ssadd (entlast) currobj))
(setq coords (list 
(list 4160.5625 818.28) 
(list 4234.585 817.93) 
(list 4234.585 818.107) 
(list 4160.5625 818.357)))
(apply 'command (append '("pline") coords '("c")))
(setq currobj (ssadd (entlast) currobj))
(setq coords (list 
(list 4160.5625 818.5) 
(list 4234.585 818.25) 
(list 4234.585 818.427) 
(list 4160.5625 818.577)))
(apply 'command (append '("pline") coords '("c")))
(setq currobj (ssadd (entlast) currobj))
(setq coords (list 
(list 4160.5625 818.72) 
(list 4234.585 818.57) 
(list 4234.585 818.747) 
(list 4160.5625 818.797)))
(apply 'command (append '("pline") coords '("c")))
(setq currobj (ssadd (entlast) currobj))
(setq coords (list 
(list 4160.5625 818.94) 
(list 4234.585 818.89) 
(list 4234.585 819.067) 
(list 4160.5625 819.017)))
(apply 'command (append '("pline") coords '("c")))
(setq currobj (ssadd (entlast) currobj))
(setq coords (list 
(list 4160.5625 819.16) 
(list 4234.585 819.21) 
(list 4234.585 819.387) 
(list 4160.5625 819.237)))
(apply 'command (append '("pline") coords '("c")))
(setq currobj (ssadd (entlast) currobj))
(setq coords (list 
(list 4160.5625 819.38) 
(list 4234.585 819.53) 
(list 4234.585 819.707) 
(list 4160.5625 819.457)))
(apply 'command (append '("pline") coords '("c")))
(setq currobj (ssadd (entlast) currobj))
(setq coords (list 
(list 4160.5625 819.6) 
(list 4234.585 819.85) 
(list 4234.585 820.027) 
(list 4160.5625 819.677)))
(apply 'command (append '("pline") coords '("c")))
(setq currobj (ssadd (entlast) currobj))
(setq coords (list 
(list 4160.5625 819.82) 
(list 4234.585 820.17) 
(list 4234.585 820.347) 
(list 4160.5625 819.897)))
(apply 'command (append '("pline") coords '("c")))
(setq currobj (ssadd (entlast) currobj))
(setq coords (list 
(list 4160.5625 820.04) 
(list 4234.585 820.49) 
(list 4234.585 820.667) 
(list 4160.5625 820.117)))
(apply 'command (append '("pline") coords '("c")))
(setq currobj (ssadd (entlast) currobj))
(setq coords (list 
(list 4160.5625 820.26) 
(list 4234.585 820.81) 
(list 4234.585 820.987) 
(list 4160.5625 820.337)))
(apply 'command (append '("pline") coords '("c")))
(setq currobj (ssadd (entlast) currobj))
(setq coords (list 
(list 4160.5625 820.48) 
(list 4234.585 821.13) 
(list 4234.585 821.307) 
(list 4160.5625 820.557)))
(apply 'command (append '("pline") coords '("c")))
(setq currobj (ssadd (entlast) currobj))
(setq coords (list 
(list 4159.4375 820.557) 
(list 4085.415 821.307) 
(list 4085.415 821.13) 
(list 4159.4375 820.48)))
(apply 'command (append '("pline") coords '("c")))
(setq currobj (ssadd (entlast) currobj))
(setq coords (list 
(list 4159.4375 820.337) 
(list 4085.415 820.987) 
(list 4085.415 820.81) 
(list 4159.4375 820.26)))
(apply 'command (append '("pline") coords '("c")))
(setq currobj (ssadd (entlast) currobj))
(setq coords (list 
(list 4159.4375 820.117) 
(list 4085.415 820.667) 
(list 4085.415 820.49) 
(list 4159.4375 820.04)))
(apply 'command (append '("pline") coords '("c")))
(setq currobj (ssadd (entlast) currobj))
(setq coords (list 
(list 4159.4375 819.897) 
(list 4085.415 820.347) 
(list 4085.415 820.17) 
(list 4159.4375 819.82)))
(apply 'command (append '("pline") coords '("c")))
(setq currobj (ssadd (entlast) currobj))
(setq coords (list 
(list 4159.4375 819.677) 
(list 4085.415 820.027) 
(list 4085.415 819.85) 
(list 4159.4375 819.6)))
(apply 'command (append '("pline") coords '("c")))
(setq currobj (ssadd (entlast) currobj))
(setq coords (list 
(list 4159.4375 819.457) 
(list 4085.415 819.707) 
(list 4085.415 819.53) 
(list 4159.4375 819.38)))
(apply 'command (append '("pline") coords '("c")))
(setq currobj (ssadd (entlast) currobj))
(setq coords (list 
(list 4159.4375 819.237) 
(list 4085.415 819.387) 
(list 4085.415 819.21) 
(list 4159.4375 819.16)))
(apply 'command (append '("pline") coords '("c")))
(setq currobj (ssadd (entlast) currobj))
(setq coords (list 
(list 4159.4375 819.017) 
(list 4085.415 819.067) 
(list 4085.415 818.89) 
(list 4159.4375 818.94)))
(apply 'command (append '("pline") coords '("c")))
(setq currobj (ssadd (entlast) currobj))
(setq coords (list 
(list 4159.4375 818.797) 
(list 4085.415 818.747) 
(list 4085.415 818.57) 
(list 4159.4375 818.72)))
(apply 'command (append '("pline") coords '("c")))
(setq currobj (ssadd (entlast) currobj))
(setq coords (list 
(list 4159.4375 818.577) 
(list 4085.415 818.427) 
(list 4085.415 818.25) 
(list 4159.4375 818.5)))
(apply 'command (append '("pline") coords '("c")))
(setq currobj (ssadd (entlast) currobj))
(setq coords (list 
(list 4159.4375 818.357) 
(list 4085.415 818.107) 
(list 4085.415 817.93) 
(list 4159.4375 818.28)))
(apply 'command (append '("pline") coords '("c")))
(setq currobj (ssadd (entlast) currobj))
(setq coords (list 
(list 4159.4375 818.137) 
(list 4085.415 817.787) 
(list 4085.415 817.61) 
(list 4159.4375 818.06)))
(apply 'command (append '("pline") coords '("c")))
(setq currobj (ssadd (entlast) currobj))
(setq coords (list 
(list 4159.4375 817.917) 
(list 4085.415 817.467) 
(list 4085.415 817.29) 
(list 4159.4375 817.84)))
(apply 'command (append '("pline") coords '("c")))
(setq currobj (ssadd (entlast) currobj))
(setq coords (list 
(list 4159.4375 817.697) 
(list 4085.415 817.147) 
(list 4085.415 816.97) 
(list 4159.4375 817.62)))
(apply 'command (append '("pline") coords '("c")))
(setq currobj (ssadd (entlast) currobj))
(setq coords (list 
(list 4159.4375 817.477) 
(list 4085.415 816.827) 
(list 4085.415 816.65) 
(list 4159.4375 817.4)))
(apply 'command (append '("pline") coords '("c")))
(setq currobj (ssadd (entlast) currobj))
(command "_layer" "set" "nitride" "")
(command "_layer" "set" "text" "")
(command "_circle" "4159.0625,806.257" "0.075")
(command "_circle" "4159.0625,806.557" "0.075")
(command "_circle" "4159.0625,806.857" "0.075")
(command "_circle" "4159.0625,807.157" "0.075")
(command "_circle" "4159.0625,807.457" "0.075")
(command "_circle" "4158.7625,806.257" "0.075")
(command "_circle" "4158.7625,806.557" "0.075")
(command "_circle" "4158.7625,806.857" "0.075")
(command "_circle" "4158.7625,807.157" "0.075")
(command "_circle" "4158.7625,807.457" "0.075")
(command "_circle" "4158.4625,806.257" "0.075")
(command "_circle" "4158.4625,806.557" "0.075")
(command "_circle" "4158.4625,806.857" "0.075")
(command "_circle" "4158.4625,807.157" "0.075")
(command "_circle" "4158.4625,807.457" "0.075")
(command "_circle" "4158.1625,806.257" "0.075")
(command "_circle" "4158.1625,806.557" "0.075")
(command "_circle" "4158.1625,806.857" "0.075")
(command "_circle" "4158.1625,807.157" "0.075")
(command "_circle" "4158.1625,807.457" "0.075")
(command "_circle" "4157.8625,806.257" "0.075")
(command "_circle" "4157.8625,806.557" "0.075")
(command "_circle" "4157.8625,806.857" "0.075")
(command "_circle" "4157.8625,807.157" "0.075")
(command "_circle" "4157.8625,807.457" "0.075")
(command "_layer" "set" "nitride" "")
(setq coords (list 
(list 4160.2625 831.7) 
(list 4160.2625 836.7) 
(list 4159.7375 836.7) 
(list 4159.7375 831.7)))
(apply 'command (append '("pline") coords '("c")))
(setq currobj (ssadd (entlast) currobj))
(command "_layer" "set" "prebias" "")
(command "_rectangle" "4159.7375,831.7" "4160.2625,836.7")
(setq currobj (ssadd (entlast) currobj))
(command "_layer" "set" "nitride" "")
(setq cooledsinglenanobeam13 currobj)
(setq currobj nil)
(setq currobj (ssadd))
; DRAWING PHOTONIC CRYSTAL
(command "_layer" "set" "negYjunc" "")
(setq coords (list 
(list 4160.135 866.7) 
(list 4160 851.7) 
(list 4160 866.7)))
(apply 'command (append '("pline") coords '("c")))
(setq currobj (ssadd (entlast) currobj))
(setq coords (list 
(list 4160.2625 836.7) 
(list 4160.415 866.7) 
(list 4161.096 866.7) 
(list 4161.096 836.7)))
(apply 'command (append '("pline") coords '("c")))
(setq currobj (ssadd (entlast) currobj))
(setq coords (list 
(list 4159.865 866.7) 
(list 4160 851.7) 
(list 4160 866.7)))
(apply 'command (append '("pline") coords '("c")))
(setq currobj (ssadd (entlast) currobj))
(setq coords (list 
(list 4159.7375 836.7) 
(list 4159.585 866.7) 
(list 4158.904 866.7) 
(list 4158.904 836.7)))
(apply 'command (append '("pline") coords '("c")))
(setq currobj (ssadd (entlast) currobj))
(command "_layer" "set" "nitride" "")
(setq yjunction13 currobj)
(setq currobj nil)
(setq currobj (ssadd))
(setq tap13 nil)
(setq tap13 (ssadd))
(command "_layer" "set" "phc" "")
(setq coords (list 
(list 4160 866.7) 
(list 4160.135 866.7) 
(list 4160.135 866.7103) 
(list 4160.135 866.7206) 
(list 4160.135 866.7308) 
(list 4160.135 866.7411) 
(list 4160.135 866.7514) 
(list 4160.135 866.7617) 
(list 4160.135 866.7719) 
(list 4160.135 866.7822) 
(list 4160.135 866.7925) 
(list 4160.135 866.8028) 
(list 4160.135 866.8131) 
(list 4160.135 866.8233) 
(list 4160.135 866.8336) 
(list 4160.135 866.8439) 
(list 4160.135 866.8542) 
(list 4160.135 866.8644) 
(list 4160.135 866.8747) 
(list 4160.135 866.885) 
(list 4160.135 866.8953) 
(list 4160.135 866.9056) 
(list 4160.135 866.9158) 
(list 4160.135 866.9261) 
(list 4160.135 866.9364) 
(list 4160.135 866.9467) 
(list 4160.135 866.9569) 
(list 4160.135 866.9672) 
(list 4160.135 866.9775) 
(list 4160.135 866.9878) 
(list 4160.135 866.9981) 
(list 4160.135 867.0083) 
(list 4160.135 867.0186) 
(list 4160.135 867.0289) 
(list 4160.135 867.0392) 
(list 4160.135 867.0494) 
(list 4160.135 867.0597) 
(list 4160.135 867.07) 
(list 4160 867.07)))
(apply 'command (append '("pline") coords '("c")))
(setq tap13 (ssadd (entlast) tap13))
(command "_mirror" (entlast) "" "4160,900" "4160,901" "No")
(setq tap13 (ssadd (entlast) tap13))
(setq coords (list 
(list 4160.4239 866.7) 
(list 4160.415 866.7) 
(list 4160.4152 866.7103) 
(list 4160.4155 866.7206) 
(list 4160.4156 866.7308) 
(list 4160.4158 866.7411) 
(list 4160.4158 866.7514) 
(list 4160.4158 866.7617) 
(list 4160.4157 866.7719) 
(list 4160.4155 866.7822) 
(list 4160.4152 866.7925) 
(list 4160.4148 866.8028) 
(list 4160.4144 866.8131) 
(list 4160.4139 866.8233) 
(list 4160.4134 866.8336) 
(list 4160.4129 866.8439) 
(list 4160.4124 866.8542) 
(list 4160.4119 866.8644) 
(list 4160.4116 866.8747) 
(list 4160.4113 866.885) 
(list 4160.4112 866.8953) 
(list 4160.4112 866.9056) 
(list 4160.4113 866.9158) 
(list 4160.4116 866.9261) 
(list 4160.4121 866.9364) 
(list 4160.4128 866.9467) 
(list 4160.4136 866.9569) 
(list 4160.4145 866.9672) 
(list 4160.4155 866.9775) 
(list 4160.4167 866.9878) 
(list 4160.4178 866.9981) 
(list 4160.419 867.0083) 
(list 4160.4201 867.0186) 
(list 4160.4212 867.0289) 
(list 4160.4221 867.0392) 
(list 4160.4229 867.0494) 
(list 4160.4235 867.0597) 
(list 4160.4239 867.07) 
(list 4160.4239 867.07)))
(apply 'command (append '("pline") coords '("c")))
(setq tap13 (ssadd (entlast) tap13))
(command "_mirror" (entlast) "" "4160,900" "4160,901" "No")
(setq tap13 (ssadd (entlast) tap13))
(setq coords (list 
(list 4161.096 866.7) 
(list 4160.4239 866.7) 
(list 4160.4239 866.7103) 
(list 4160.4239 866.7206) 
(list 4160.4239 866.7308) 
(list 4160.4239 866.7411) 
(list 4160.4239 866.7514) 
(list 4160.4239 866.7617) 
(list 4160.4239 866.7719) 
(list 4160.4239 866.7822) 
(list 4160.4239 866.7925) 
(list 4160.4239 866.8028) 
(list 4160.4239 866.8131) 
(list 4160.4239 866.8233) 
(list 4160.4239 866.8336) 
(list 4160.4239 866.8439) 
(list 4160.4239 866.8542) 
(list 4160.4239 866.8644) 
(list 4160.4239 866.8747) 
(list 4160.4239 866.885) 
(list 4160.4239 866.8953) 
(list 4160.4239 866.9056) 
(list 4160.4239 866.9158) 
(list 4160.4239 866.9261) 
(list 4160.4239 866.9364) 
(list 4160.4239 866.9467) 
(list 4160.4239 866.9569) 
(list 4160.4239 866.9672) 
(list 4160.4239 866.9775) 
(list 4160.4239 866.9878) 
(list 4160.4239 866.9981) 
(list 4160.4239 867.0083) 
(list 4160.4239 867.0186) 
(list 4160.4239 867.0289) 
(list 4160.4239 867.0392) 
(list 4160.4239 867.0494) 
(list 4160.4239 867.0597) 
(list 4160.4239 867.07) 
(list 4161.096 867.07)))
(apply 'command (append '("pline") coords '("c")))
(setq tap13 (ssadd (entlast) tap13))
(command "_mirror" (entlast) "" "4160,900" "4160,901" "No")
(setq tap13 (ssadd (entlast) tap13))
(setq coords (list 
(list 4160 867.07) 
(list 4160.135 867.07) 
(list 4160.135 867.0803) 
(list 4160.135 867.0906) 
(list 4160.135 867.1008) 
(list 4160.135 867.1111) 
(list 4160.135 867.1214) 
(list 4160.135 867.1317) 
(list 4160.135 867.1419) 
(list 4160.135 867.1522) 
(list 4160.135 867.1625) 
(list 4160.135 867.1728) 
(list 4160.135 867.1831) 
(list 4160.135 867.1933) 
(list 4160.135 867.2036) 
(list 4160.135 867.2139) 
(list 4160.135 867.2242) 
(list 4160.135 867.2344) 
(list 4160.135 867.2447) 
(list 4160.135 867.255) 
(list 4160.135 867.2653) 
(list 4160.135 867.2756) 
(list 4160.135 867.2858) 
(list 4160.135 867.2961) 
(list 4160.135 867.3064) 
(list 4160.135 867.3167) 
(list 4160.135 867.3269) 
(list 4160.135 867.3372) 
(list 4160.135 867.3475) 
(list 4160.135 867.3578) 
(list 4160.135 867.3681) 
(list 4160.135 867.3783) 
(list 4160.135 867.3886) 
(list 4160.135 867.3989) 
(list 4160.135 867.4092) 
(list 4160.135 867.4194) 
(list 4160.135 867.4297) 
(list 4160.135 867.44) 
(list 4160 867.44)))
(apply 'command (append '("pline") coords '("c")))
(setq tap13 (ssadd (entlast) tap13))
(command "_mirror" (entlast) "" "4160,900" "4160,901" "No")
(setq tap13 (ssadd (entlast) tap13))
(setq coords (list 
(list 4160.4327 867.07) 
(list 4160.4239 867.07) 
(list 4160.424 867.0803) 
(list 4160.4238 867.0906) 
(list 4160.4234 867.1008) 
(list 4160.4227 867.1111) 
(list 4160.4218 867.1214) 
(list 4160.4206 867.1317) 
(list 4160.4192 867.1419) 
(list 4160.4176 867.1522) 
(list 4160.4159 867.1625) 
(list 4160.4141 867.1728) 
(list 4160.4123 867.1831) 
(list 4160.4106 867.1933) 
(list 4160.4089 867.2036) 
(list 4160.4074 867.2139) 
(list 4160.4061 867.2242) 
(list 4160.405 867.2344) 
(list 4160.4043 867.2447) 
(list 4160.4039 867.255) 
(list 4160.4039 867.2653) 
(list 4160.4043 867.2756) 
(list 4160.405 867.2858) 
(list 4160.4061 867.2961) 
(list 4160.4076 867.3064) 
(list 4160.4094 867.3167) 
(list 4160.4115 867.3269) 
(list 4160.4138 867.3372) 
(list 4160.4163 867.3475) 
(list 4160.4188 867.3578) 
(list 4160.4213 867.3681) 
(list 4160.4238 867.3783) 
(list 4160.4261 867.3886) 
(list 4160.4282 867.3989) 
(list 4160.4299 867.4092) 
(list 4160.4313 867.4194) 
(list 4160.4322 867.4297) 
(list 4160.4327 867.44) 
(list 4160.4327 867.44)))
(apply 'command (append '("pline") coords '("c")))
(setq tap13 (ssadd (entlast) tap13))
(command "_mirror" (entlast) "" "4160,900" "4160,901" "No")
(setq tap13 (ssadd (entlast) tap13))
(setq coords (list 
(list 4161.096 867.07) 
(list 4160.4327 867.07) 
(list 4160.4327 867.0803) 
(list 4160.4327 867.0906) 
(list 4160.4327 867.1008) 
(list 4160.4327 867.1111) 
(list 4160.4327 867.1214) 
(list 4160.4327 867.1317) 
(list 4160.4327 867.1419) 
(list 4160.4327 867.1522) 
(list 4160.4327 867.1625) 
(list 4160.4327 867.1728) 
(list 4160.4327 867.1831) 
(list 4160.4327 867.1933) 
(list 4160.4327 867.2036) 
(list 4160.4327 867.2139) 
(list 4160.4327 867.2242) 
(list 4160.4327 867.2344) 
(list 4160.4327 867.2447) 
(list 4160.4327 867.255) 
(list 4160.4327 867.2653) 
(list 4160.4327 867.2756) 
(list 4160.4327 867.2858) 
(list 4160.4327 867.2961) 
(list 4160.4327 867.3064) 
(list 4160.4327 867.3167) 
(list 4160.4327 867.3269) 
(list 4160.4327 867.3372) 
(list 4160.4327 867.3475) 
(list 4160.4327 867.3578) 
(list 4160.4327 867.3681) 
(list 4160.4327 867.3783) 
(list 4160.4327 867.3886) 
(list 4160.4327 867.3989) 
(list 4160.4327 867.4092) 
(list 4160.4327 867.4194) 
(list 4160.4327 867.4297) 
(list 4160.4327 867.44) 
(list 4161.096 867.44)))
(apply 'command (append '("pline") coords '("c")))
(setq tap13 (ssadd (entlast) tap13))
(command "_mirror" (entlast) "" "4160,900" "4160,901" "No")
(setq tap13 (ssadd (entlast) tap13))
(setq coords (list 
(list 4160 867.44) 
(list 4160.135 867.44) 
(list 4160.135 867.4503) 
(list 4160.135 867.4606) 
(list 4160.135 867.4708) 
(list 4160.135 867.4811) 
(list 4160.135 867.4914) 
(list 4160.135 867.5017) 
(list 4160.135 867.5119) 
(list 4160.135 867.5222) 
(list 4160.135 867.5325) 
(list 4160.135 867.5428) 
(list 4160.135 867.5531) 
(list 4160.135 867.5633) 
(list 4160.135 867.5736) 
(list 4160.135 867.5839) 
(list 4160.135 867.5942) 
(list 4160.135 867.6044) 
(list 4160.135 867.6147) 
(list 4160.135 867.625) 
(list 4160.135 867.6353) 
(list 4160.135 867.6456) 
(list 4160.135 867.6558) 
(list 4160.135 867.6661) 
(list 4160.135 867.6764) 
(list 4160.135 867.6867) 
(list 4160.135 867.6969) 
(list 4160.135 867.7072) 
(list 4160.135 867.7175) 
(list 4160.135 867.7278) 
(list 4160.135 867.7381) 
(list 4160.135 867.7483) 
(list 4160.135 867.7586) 
(list 4160.135 867.7689) 
(list 4160.135 867.7792) 
(list 4160.135 867.7894) 
(list 4160.135 867.7997) 
(list 4160.135 867.81) 
(list 4160 867.81)))
(apply 'command (append '("pline") coords '("c")))
(setq tap13 (ssadd (entlast) tap13))
(command "_mirror" (entlast) "" "4160,900" "4160,901" "No")
(setq tap13 (ssadd (entlast) tap13))
(setq coords (list 
(list 4160.4416 867.44) 
(list 4160.4327 867.44) 
(list 4160.4327 867.4503) 
(list 4160.4322 867.4606) 
(list 4160.4312 867.4708) 
(list 4160.4297 867.4811) 
(list 4160.4278 867.4914) 
(list 4160.4254 867.5017) 
(list 4160.4227 867.5119) 
(list 4160.4198 867.5222) 
(list 4160.4167 867.5325) 
(list 4160.4135 867.5428) 
(list 4160.4103 867.5531) 
(list 4160.4072 867.5633) 
(list 4160.4044 867.5736) 
(list 4160.4019 867.5839) 
(list 4160.3997 867.5942) 
(list 4160.3981 867.6044) 
(list 4160.397 867.6147) 
(list 4160.3965 867.625) 
(list 4160.3966 867.6353) 
(list 4160.3973 867.6456) 
(list 4160.3987 867.6558) 
(list 4160.4006 867.6661) 
(list 4160.4031 867.6764) 
(list 4160.4061 867.6867) 
(list 4160.4095 867.6969) 
(list 4160.4132 867.7072) 
(list 4160.417 867.7175) 
(list 4160.421 867.7278) 
(list 4160.4249 867.7381) 
(list 4160.4286 867.7483) 
(list 4160.4321 867.7586) 
(list 4160.4351 867.7689) 
(list 4160.4377 867.7792) 
(list 4160.4397 867.7894) 
(list 4160.441 867.7997) 
(list 4160.4416 867.81) 
(list 4160.4416 867.81)))
(apply 'command (append '("pline") coords '("c")))
(setq tap13 (ssadd (entlast) tap13))
(command "_mirror" (entlast) "" "4160,900" "4160,901" "No")
(setq tap13 (ssadd (entlast) tap13))
(setq coords (list 
(list 4161.096 867.44) 
(list 4160.4416 867.44) 
(list 4160.4416 867.4503) 
(list 4160.4416 867.4606) 
(list 4160.4416 867.4708) 
(list 4160.4416 867.4811) 
(list 4160.4416 867.4914) 
(list 4160.4416 867.5017) 
(list 4160.4416 867.5119) 
(list 4160.4416 867.5222) 
(list 4160.4416 867.5325) 
(list 4160.4416 867.5428) 
(list 4160.4416 867.5531) 
(list 4160.4416 867.5633) 
(list 4160.4416 867.5736) 
(list 4160.4416 867.5839) 
(list 4160.4416 867.5942) 
(list 4160.4416 867.6044) 
(list 4160.4416 867.6147) 
(list 4160.4416 867.625) 
(list 4160.4416 867.6353) 
(list 4160.4416 867.6456) 
(list 4160.4416 867.6558) 
(list 4160.4416 867.6661) 
(list 4160.4416 867.6764) 
(list 4160.4416 867.6867) 
(list 4160.4416 867.6969) 
(list 4160.4416 867.7072) 
(list 4160.4416 867.7175) 
(list 4160.4416 867.7278) 
(list 4160.4416 867.7381) 
(list 4160.4416 867.7483) 
(list 4160.4416 867.7586) 
(list 4160.4416 867.7689) 
(list 4160.4416 867.7792) 
(list 4160.4416 867.7894) 
(list 4160.4416 867.7997) 
(list 4160.4416 867.81) 
(list 4161.096 867.81)))
(apply 'command (append '("pline") coords '("c")))
(setq tap13 (ssadd (entlast) tap13))
(command "_mirror" (entlast) "" "4160,900" "4160,901" "No")
(setq tap13 (ssadd (entlast) tap13))
(setq coords (list 
(list 4160 867.81) 
(list 4160.135 867.81) 
(list 4160.135 867.8203) 
(list 4160.135 867.8306) 
(list 4160.135 867.8408) 
(list 4160.135 867.8511) 
(list 4160.135 867.8614) 
(list 4160.135 867.8717) 
(list 4160.135 867.8819) 
(list 4160.135 867.8922) 
(list 4160.135 867.9025) 
(list 4160.135 867.9128) 
(list 4160.135 867.9231) 
(list 4160.135 867.9333) 
(list 4160.135 867.9436) 
(list 4160.135 867.9539) 
(list 4160.135 867.9642) 
(list 4160.135 867.9744) 
(list 4160.135 867.9847) 
(list 4160.135 867.995) 
(list 4160.135 868.0053) 
(list 4160.135 868.0156) 
(list 4160.135 868.0258) 
(list 4160.135 868.0361) 
(list 4160.135 868.0464) 
(list 4160.135 868.0567) 
(list 4160.135 868.0669) 
(list 4160.135 868.0772) 
(list 4160.135 868.0875) 
(list 4160.135 868.0978) 
(list 4160.135 868.1081) 
(list 4160.135 868.1183) 
(list 4160.135 868.1286) 
(list 4160.135 868.1389) 
(list 4160.135 868.1492) 
(list 4160.135 868.1594) 
(list 4160.135 868.1697) 
(list 4160.135 868.18) 
(list 4160 868.18)))
(apply 'command (append '("pline") coords '("c")))
(setq tap13 (ssadd (entlast) tap13))
(command "_mirror" (entlast) "" "4160,900" "4160,901" "No")
(setq tap13 (ssadd (entlast) tap13))
(setq coords (list 
(list 4160.4505 867.81) 
(list 4160.4416 867.81) 
(list 4160.4415 867.8203) 
(list 4160.4406 867.8306) 
(list 4160.439 867.8408) 
(list 4160.4367 867.8511) 
(list 4160.4337 867.8614) 
(list 4160.4302 867.8717) 
(list 4160.4262 867.8819) 
(list 4160.4219 867.8922) 
(list 4160.4174 867.9025) 
(list 4160.4128 867.9128) 
(list 4160.4082 867.9231) 
(list 4160.4039 867.9333) 
(list 4160.3999 867.9436) 
(list 4160.3964 867.9539) 
(list 4160.3934 867.9642) 
(list 4160.3912 867.9744) 
(list 4160.3897 867.9847) 
(list 4160.3891 867.995) 
(list 4160.3893 868.0053) 
(list 4160.3904 868.0156) 
(list 4160.3924 868.0258) 
(list 4160.3951 868.0361) 
(list 4160.3986 868.0464) 
(list 4160.4028 868.0567) 
(list 4160.4074 868.0669) 
(list 4160.4125 868.0772) 
(list 4160.4177 868.0875) 
(list 4160.4231 868.0978) 
(list 4160.4284 868.1081) 
(list 4160.4334 868.1183) 
(list 4160.438 868.1286) 
(list 4160.4421 868.1389) 
(list 4160.4455 868.1492) 
(list 4160.448 868.1594) 
(list 4160.4497 868.1697) 
(list 4160.4505 868.18) 
(list 4160.4505 868.18)))
(apply 'command (append '("pline") coords '("c")))
(setq tap13 (ssadd (entlast) tap13))
(command "_mirror" (entlast) "" "4160,900" "4160,901" "No")
(setq tap13 (ssadd (entlast) tap13))
(setq coords (list 
(list 4161.096 867.81) 
(list 4160.4505 867.81) 
(list 4160.4505 867.8203) 
(list 4160.4505 867.8306) 
(list 4160.4505 867.8408) 
(list 4160.4505 867.8511) 
(list 4160.4505 867.8614) 
(list 4160.4505 867.8717) 
(list 4160.4505 867.8819) 
(list 4160.4505 867.8922) 
(list 4160.4505 867.9025) 
(list 4160.4505 867.9128) 
(list 4160.4505 867.9231) 
(list 4160.4505 867.9333) 
(list 4160.4505 867.9436) 
(list 4160.4505 867.9539) 
(list 4160.4505 867.9642) 
(list 4160.4505 867.9744) 
(list 4160.4505 867.9847) 
(list 4160.4505 867.995) 
(list 4160.4505 868.0053) 
(list 4160.4505 868.0156) 
(list 4160.4505 868.0258) 
(list 4160.4505 868.0361) 
(list 4160.4505 868.0464) 
(list 4160.4505 868.0567) 
(list 4160.4505 868.0669) 
(list 4160.4505 868.0772) 
(list 4160.4505 868.0875) 
(list 4160.4505 868.0978) 
(list 4160.4505 868.1081) 
(list 4160.4505 868.1183) 
(list 4160.4505 868.1286) 
(list 4160.4505 868.1389) 
(list 4160.4505 868.1492) 
(list 4160.4505 868.1594) 
(list 4160.4505 868.1697) 
(list 4160.4505 868.18) 
(list 4161.096 868.18)))
(apply 'command (append '("pline") coords '("c")))
(setq tap13 (ssadd (entlast) tap13))
(command "_mirror" (entlast) "" "4160,900" "4160,901" "No")
(setq tap13 (ssadd (entlast) tap13))
(setq coords (list 
(list 4160 868.18) 
(list 4160.135 868.18) 
(list 4160.135 868.1903) 
(list 4160.135 868.2006) 
(list 4160.135 868.2108) 
(list 4160.135 868.2211) 
(list 4160.135 868.2314) 
(list 4160.135 868.2417) 
(list 4160.135 868.2519) 
(list 4160.135 868.2622) 
(list 4160.135 868.2725) 
(list 4160.135 868.2828) 
(list 4160.135 868.2931) 
(list 4160.135 868.3033) 
(list 4160.135 868.3136) 
(list 4160.135 868.3239) 
(list 4160.135 868.3342) 
(list 4160.135 868.3444) 
(list 4160.135 868.3547) 
(list 4160.135 868.365) 
(list 4160.135 868.3753) 
(list 4160.135 868.3856) 
(list 4160.135 868.3958) 
(list 4160.135 868.4061) 
(list 4160.135 868.4164) 
(list 4160.135 868.4267) 
(list 4160.135 868.4369) 
(list 4160.135 868.4472) 
(list 4160.135 868.4575) 
(list 4160.135 868.4678) 
(list 4160.135 868.4781) 
(list 4160.135 868.4883) 
(list 4160.135 868.4986) 
(list 4160.135 868.5089) 
(list 4160.135 868.5192) 
(list 4160.135 868.5294) 
(list 4160.135 868.5397) 
(list 4160.135 868.55) 
(list 4160 868.55)))
(apply 'command (append '("pline") coords '("c")))
(setq tap13 (ssadd (entlast) tap13))
(command "_mirror" (entlast) "" "4160,900" "4160,901" "No")
(setq tap13 (ssadd (entlast) tap13))
(setq coords (list 
(list 4160.4593 868.18) 
(list 4160.4505 868.18) 
(list 4160.4502 868.1903) 
(list 4160.449 868.2006) 
(list 4160.4468 868.2108) 
(list 4160.4436 868.2211) 
(list 4160.4397 868.2314) 
(list 4160.435 868.2417) 
(list 4160.4297 868.2519) 
(list 4160.4241 868.2622) 
(list 4160.4181 868.2725) 
(list 4160.4121 868.2828) 
(list 4160.4062 868.2931) 
(list 4160.4006 868.3033) 
(list 4160.3954 868.3136) 
(list 4160.3909 868.3239) 
(list 4160.3871 868.3342) 
(list 4160.3843 868.3444) 
(list 4160.3825 868.3547) 
(list 4160.3817 868.365) 
(list 4160.3821 868.3753) 
(list 4160.3835 868.3856) 
(list 4160.3861 868.3958) 
(list 4160.3897 868.4061) 
(list 4160.3942 868.4164) 
(list 4160.3994 868.4267) 
(list 4160.4054 868.4369) 
(list 4160.4118 868.4472) 
(list 4160.4185 868.4575) 
(list 4160.4253 868.4678) 
(list 4160.4319 868.4781) 
(list 4160.4382 868.4883) 
(list 4160.444 868.4986) 
(list 4160.449 868.5089) 
(list 4160.4532 868.5192) 
(list 4160.4564 868.5294) 
(list 4160.4585 868.5397) 
(list 4160.4593 868.55) 
(list 4160.4593 868.55)))
(apply 'command (append '("pline") coords '("c")))
(setq tap13 (ssadd (entlast) tap13))
(command "_mirror" (entlast) "" "4160,900" "4160,901" "No")
(setq tap13 (ssadd (entlast) tap13))
(setq coords (list 
(list 4161.096 868.18) 
(list 4160.4593 868.18) 
(list 4160.4593 868.1903) 
(list 4160.4593 868.2006) 
(list 4160.4593 868.2108) 
(list 4160.4593 868.2211) 
(list 4160.4593 868.2314) 
(list 4160.4593 868.2417) 
(list 4160.4593 868.2519) 
(list 4160.4593 868.2622) 
(list 4160.4593 868.2725) 
(list 4160.4593 868.2828) 
(list 4160.4593 868.2931) 
(list 4160.4593 868.3033) 
(list 4160.4593 868.3136) 
(list 4160.4593 868.3239) 
(list 4160.4593 868.3342) 
(list 4160.4593 868.3444) 
(list 4160.4593 868.3547) 
(list 4160.4593 868.365) 
(list 4160.4593 868.3753) 
(list 4160.4593 868.3856) 
(list 4160.4593 868.3958) 
(list 4160.4593 868.4061) 
(list 4160.4593 868.4164) 
(list 4160.4593 868.4267) 
(list 4160.4593 868.4369) 
(list 4160.4593 868.4472) 
(list 4160.4593 868.4575) 
(list 4160.4593 868.4678) 
(list 4160.4593 868.4781) 
(list 4160.4593 868.4883) 
(list 4160.4593 868.4986) 
(list 4160.4593 868.5089) 
(list 4160.4593 868.5192) 
(list 4160.4593 868.5294) 
(list 4160.4593 868.5397) 
(list 4160.4593 868.55) 
(list 4161.096 868.55)))
(apply 'command (append '("pline") coords '("c")))
(setq tap13 (ssadd (entlast) tap13))
(command "_mirror" (entlast) "" "4160,900" "4160,901" "No")
(setq tap13 (ssadd (entlast) tap13))
(setq coords (list 
(list 4160 868.55) 
(list 4160.135 868.55) 
(list 4160.135 868.5603) 
(list 4160.135 868.5706) 
(list 4160.135 868.5808) 
(list 4160.135 868.5911) 
(list 4160.135 868.6014) 
(list 4160.135 868.6117) 
(list 4160.135 868.6219) 
(list 4160.135 868.6322) 
(list 4160.135 868.6425) 
(list 4160.135 868.6528) 
(list 4160.135 868.6631) 
(list 4160.135 868.6733) 
(list 4160.135 868.6836) 
(list 4160.135 868.6939) 
(list 4160.135 868.7042) 
(list 4160.135 868.7144) 
(list 4160.135 868.7247) 
(list 4160.135 868.735) 
(list 4160.135 868.7453) 
(list 4160.135 868.7556) 
(list 4160.135 868.7658) 
(list 4160.135 868.7761) 
(list 4160.135 868.7864) 
(list 4160.135 868.7967) 
(list 4160.135 868.8069) 
(list 4160.135 868.8172) 
(list 4160.135 868.8275) 
(list 4160.135 868.8378) 
(list 4160.135 868.8481) 
(list 4160.135 868.8583) 
(list 4160.135 868.8686) 
(list 4160.135 868.8789) 
(list 4160.135 868.8892) 
(list 4160.135 868.8994) 
(list 4160.135 868.9097) 
(list 4160.135 868.92) 
(list 4160 868.92)))
(apply 'command (append '("pline") coords '("c")))
(setq tap13 (ssadd (entlast) tap13))
(command "_mirror" (entlast) "" "4160,900" "4160,901" "No")
(setq tap13 (ssadd (entlast) tap13))
(setq coords (list 
(list 4160.4682 868.55) 
(list 4160.4593 868.55) 
(list 4160.459 868.5603) 
(list 4160.4573 868.5706) 
(list 4160.4545 868.5808) 
(list 4160.4506 868.5911) 
(list 4160.4456 868.6014) 
(list 4160.4398 868.6117) 
(list 4160.4333 868.6219) 
(list 4160.4262 868.6322) 
(list 4160.4189 868.6425) 
(list 4160.4114 868.6528) 
(list 4160.4041 868.6631) 
(list 4160.3972 868.6733) 
(list 4160.3909 868.6836) 
(list 4160.3854 868.6939) 
(list 4160.3808 868.7042) 
(list 4160.3774 868.7144) 
(list 4160.3752 868.7247) 
(list 4160.3743 868.735) 
(list 4160.3748 868.7453) 
(list 4160.3766 868.7556) 
(list 4160.3798 868.7658) 
(list 4160.3842 868.7761) 
(list 4160.3897 868.7864) 
(list 4160.3961 868.7967) 
(list 4160.4033 868.8069) 
(list 4160.4111 868.8172) 
(list 4160.4192 868.8275) 
(list 4160.4274 868.8378) 
(list 4160.4354 868.8481) 
(list 4160.443 868.8583) 
(list 4160.4499 868.8686) 
(list 4160.456 868.8789) 
(list 4160.461 868.8892) 
(list 4160.4648 868.8994) 
(list 4160.4672 868.9097) 
(list 4160.4682 868.92) 
(list 4160.4682 868.92)))
(apply 'command (append '("pline") coords '("c")))
(setq tap13 (ssadd (entlast) tap13))
(command "_mirror" (entlast) "" "4160,900" "4160,901" "No")
(setq tap13 (ssadd (entlast) tap13))
(setq coords (list 
(list 4161.096 868.55) 
(list 4160.4682 868.55) 
(list 4160.4682 868.5603) 
(list 4160.4682 868.5706) 
(list 4160.4682 868.5808) 
(list 4160.4682 868.5911) 
(list 4160.4682 868.6014) 
(list 4160.4682 868.6117) 
(list 4160.4682 868.6219) 
(list 4160.4682 868.6322) 
(list 4160.4682 868.6425) 
(list 4160.4682 868.6528) 
(list 4160.4682 868.6631) 
(list 4160.4682 868.6733) 
(list 4160.4682 868.6836) 
(list 4160.4682 868.6939) 
(list 4160.4682 868.7042) 
(list 4160.4682 868.7144) 
(list 4160.4682 868.7247) 
(list 4160.4682 868.735) 
(list 4160.4682 868.7453) 
(list 4160.4682 868.7556) 
(list 4160.4682 868.7658) 
(list 4160.4682 868.7761) 
(list 4160.4682 868.7864) 
(list 4160.4682 868.7967) 
(list 4160.4682 868.8069) 
(list 4160.4682 868.8172) 
(list 4160.4682 868.8275) 
(list 4160.4682 868.8378) 
(list 4160.4682 868.8481) 
(list 4160.4682 868.8583) 
(list 4160.4682 868.8686) 
(list 4160.4682 868.8789) 
(list 4160.4682 868.8892) 
(list 4160.4682 868.8994) 
(list 4160.4682 868.9097) 
(list 4160.4682 868.92) 
(list 4161.096 868.92)))
(apply 'command (append '("pline") coords '("c")))
(setq tap13 (ssadd (entlast) tap13))
(command "_mirror" (entlast) "" "4160,900" "4160,901" "No")
(setq tap13 (ssadd (entlast) tap13))
(setq coords (list 
(list 4160 868.92) 
(list 4160.135 868.92) 
(list 4160.135 868.9303) 
(list 4160.135 868.9406) 
(list 4160.135 868.9508) 
(list 4160.135 868.9611) 
(list 4160.135 868.9714) 
(list 4160.135 868.9817) 
(list 4160.135 868.9919) 
(list 4160.135 869.0022) 
(list 4160.135 869.0125) 
(list 4160.135 869.0228) 
(list 4160.135 869.0331) 
(list 4160.135 869.0433) 
(list 4160.135 869.0536) 
(list 4160.135 869.0639) 
(list 4160.135 869.0742) 
(list 4160.135 869.0844) 
(list 4160.135 869.0947) 
(list 4160.135 869.105) 
(list 4160.135 869.1153) 
(list 4160.135 869.1256) 
(list 4160.135 869.1358) 
(list 4160.135 869.1461) 
(list 4160.135 869.1564) 
(list 4160.135 869.1667) 
(list 4160.135 869.1769) 
(list 4160.135 869.1872) 
(list 4160.135 869.1975) 
(list 4160.135 869.2078) 
(list 4160.135 869.2181) 
(list 4160.135 869.2283) 
(list 4160.135 869.2386) 
(list 4160.135 869.2489) 
(list 4160.135 869.2592) 
(list 4160.135 869.2694) 
(list 4160.135 869.2797) 
(list 4160.135 869.29) 
(list 4160 869.29)))
(apply 'command (append '("pline") coords '("c")))
(setq tap13 (ssadd (entlast) tap13))
(command "_mirror" (entlast) "" "4160,900" "4160,901" "No")
(setq tap13 (ssadd (entlast) tap13))
(setq coords (list 
(list 4160.4771 868.92) 
(list 4160.4682 868.92) 
(list 4160.4677 868.9303) 
(list 4160.4657 868.9406) 
(list 4160.4623 868.9508) 
(list 4160.4576 868.9611) 
(list 4160.4516 868.9714) 
(list 4160.4446 868.9817) 
(list 4160.4368 868.9919) 
(list 4160.4284 869.0022) 
(list 4160.4196 869.0125) 
(list 4160.4107 869.0228) 
(list 4160.4021 869.0331) 
(list 4160.3939 869.0433) 
(list 4160.3864 869.0536) 
(list 4160.3799 869.0639) 
(list 4160.3745 869.0742) 
(list 4160.3705 869.0844) 
(list 4160.3679 869.0947) 
(list 4160.3669 869.105) 
(list 4160.3675 869.1153) 
(list 4160.3697 869.1256) 
(list 4160.3735 869.1358) 
(list 4160.3787 869.1461) 
(list 4160.3852 869.1564) 
(list 4160.3928 869.1667) 
(list 4160.4013 869.1769) 
(list 4160.4104 869.1872) 
(list 4160.42 869.1975) 
(list 4160.4295 869.2078) 
(list 4160.4389 869.2181) 
(list 4160.4478 869.2283) 
(list 4160.4559 869.2386) 
(list 4160.463 869.2489) 
(list 4160.4688 869.2592) 
(list 4160.4732 869.2694) 
(list 4160.476 869.2797) 
(list 4160.4771 869.29) 
(list 4160.4771 869.29)))
(apply 'command (append '("pline") coords '("c")))
(setq tap13 (ssadd (entlast) tap13))
(command "_mirror" (entlast) "" "4160,900" "4160,901" "No")
(setq tap13 (ssadd (entlast) tap13))
(setq coords (list 
(list 4161.096 868.92) 
(list 4160.4771 868.92) 
(list 4160.4771 868.9303) 
(list 4160.4771 868.9406) 
(list 4160.4771 868.9508) 
(list 4160.4771 868.9611) 
(list 4160.4771 868.9714) 
(list 4160.4771 868.9817) 
(list 4160.4771 868.9919) 
(list 4160.4771 869.0022) 
(list 4160.4771 869.0125) 
(list 4160.4771 869.0228) 
(list 4160.4771 869.0331) 
(list 4160.4771 869.0433) 
(list 4160.4771 869.0536) 
(list 4160.4771 869.0639) 
(list 4160.4771 869.0742) 
(list 4160.4771 869.0844) 
(list 4160.4771 869.0947) 
(list 4160.4771 869.105) 
(list 4160.4771 869.1153) 
(list 4160.4771 869.1256) 
(list 4160.4771 869.1358) 
(list 4160.4771 869.1461) 
(list 4160.4771 869.1564) 
(list 4160.4771 869.1667) 
(list 4160.4771 869.1769) 
(list 4160.4771 869.1872) 
(list 4160.4771 869.1975) 
(list 4160.4771 869.2078) 
(list 4160.4771 869.2181) 
(list 4160.4771 869.2283) 
(list 4160.4771 869.2386) 
(list 4160.4771 869.2489) 
(list 4160.4771 869.2592) 
(list 4160.4771 869.2694) 
(list 4160.4771 869.2797) 
(list 4160.4771 869.29) 
(list 4161.096 869.29)))
(apply 'command (append '("pline") coords '("c")))
(setq tap13 (ssadd (entlast) tap13))
(command "_mirror" (entlast) "" "4160,900" "4160,901" "No")
(setq tap13 (ssadd (entlast) tap13))
(setq coords (list 
(list 4160 869.29) 
(list 4160.135 869.29) 
(list 4160.135 869.3003) 
(list 4160.135 869.3106) 
(list 4160.135 869.3208) 
(list 4160.135 869.3311) 
(list 4160.135 869.3414) 
(list 4160.135 869.3517) 
(list 4160.135 869.3619) 
(list 4160.135 869.3722) 
(list 4160.135 869.3825) 
(list 4160.135 869.3928) 
(list 4160.135 869.4031) 
(list 4160.135 869.4133) 
(list 4160.135 869.4236) 
(list 4160.135 869.4339) 
(list 4160.135 869.4442) 
(list 4160.135 869.4544) 
(list 4160.135 869.4647) 
(list 4160.135 869.475) 
(list 4160.135 869.4853) 
(list 4160.135 869.4956) 
(list 4160.135 869.5058) 
(list 4160.135 869.5161) 
(list 4160.135 869.5264) 
(list 4160.135 869.5367) 
(list 4160.135 869.5469) 
(list 4160.135 869.5572) 
(list 4160.135 869.5675) 
(list 4160.135 869.5778) 
(list 4160.135 869.5881) 
(list 4160.135 869.5983) 
(list 4160.135 869.6086) 
(list 4160.135 869.6189) 
(list 4160.135 869.6292) 
(list 4160.135 869.6394) 
(list 4160.135 869.6497) 
(list 4160.135 869.66) 
(list 4160 869.66)))
(apply 'command (append '("pline") coords '("c")))
(setq tap13 (ssadd (entlast) tap13))
(command "_mirror" (entlast) "" "4160,900" "4160,901" "No")
(setq tap13 (ssadd (entlast) tap13))
(setq coords (list 
(list 4160.4859 869.29) 
(list 4160.4771 869.29) 
(list 4160.4764 869.3003) 
(list 4160.4741 869.3106) 
(list 4160.4701 869.3208) 
(list 4160.4645 869.3311) 
(list 4160.4576 869.3414) 
(list 4160.4494 869.3517) 
(list 4160.4403 869.3619) 
(list 4160.4305 869.3722) 
(list 4160.4203 869.3825) 
(list 4160.4101 869.3928) 
(list 4160.4 869.4031) 
(list 4160.3906 869.4133) 
(list 4160.3819 869.4236) 
(list 4160.3744 869.4339) 
(list 4160.3682 869.4442) 
(list 4160.3636 869.4544) 
(list 4160.3606 869.4647) 
(list 4160.3595 869.475) 
(list 4160.3602 869.4853) 
(list 4160.3628 869.4956) 
(list 4160.3671 869.5058) 
(list 4160.3732 869.5161) 
(list 4160.3807 869.5264) 
(list 4160.3894 869.5367) 
(list 4160.3992 869.5469) 
(list 4160.4098 869.5572) 
(list 4160.4207 869.5675) 
(list 4160.4317 869.5778) 
(list 4160.4424 869.5881) 
(list 4160.4526 869.5983) 
(list 4160.4619 869.6086) 
(list 4160.4699 869.6189) 
(list 4160.4766 869.6292) 
(list 4160.4815 869.6394) 
(list 4160.4847 869.6497) 
(list 4160.4859 869.66) 
(list 4160.4859 869.66)))
(apply 'command (append '("pline") coords '("c")))
(setq tap13 (ssadd (entlast) tap13))
(command "_mirror" (entlast) "" "4160,900" "4160,901" "No")
(setq tap13 (ssadd (entlast) tap13))
(setq coords (list 
(list 4161.096 869.29) 
(list 4160.4859 869.29) 
(list 4160.4859 869.3003) 
(list 4160.4859 869.3106) 
(list 4160.4859 869.3208) 
(list 4160.4859 869.3311) 
(list 4160.4859 869.3414) 
(list 4160.4859 869.3517) 
(list 4160.4859 869.3619) 
(list 4160.4859 869.3722) 
(list 4160.4859 869.3825) 
(list 4160.4859 869.3928) 
(list 4160.4859 869.4031) 
(list 4160.4859 869.4133) 
(list 4160.4859 869.4236) 
(list 4160.4859 869.4339) 
(list 4160.4859 869.4442) 
(list 4160.4859 869.4544) 
(list 4160.4859 869.4647) 
(list 4160.4859 869.475) 
(list 4160.4859 869.4853) 
(list 4160.4859 869.4956) 
(list 4160.4859 869.5058) 
(list 4160.4859 869.5161) 
(list 4160.4859 869.5264) 
(list 4160.4859 869.5367) 
(list 4160.4859 869.5469) 
(list 4160.4859 869.5572) 
(list 4160.4859 869.5675) 
(list 4160.4859 869.5778) 
(list 4160.4859 869.5881) 
(list 4160.4859 869.5983) 
(list 4160.4859 869.6086) 
(list 4160.4859 869.6189) 
(list 4160.4859 869.6292) 
(list 4160.4859 869.6394) 
(list 4160.4859 869.6497) 
(list 4160.4859 869.66) 
(list 4161.096 869.66)))
(apply 'command (append '("pline") coords '("c")))
(setq tap13 (ssadd (entlast) tap13))
(command "_mirror" (entlast) "" "4160,900" "4160,901" "No")
(setq tap13 (ssadd (entlast) tap13))
(setq coords (list 
(list 4160 869.66) 
(list 4160.135 869.66) 
(list 4160.135 869.6703) 
(list 4160.135 869.6806) 
(list 4160.135 869.6908) 
(list 4160.135 869.7011) 
(list 4160.135 869.7114) 
(list 4160.135 869.7217) 
(list 4160.135 869.7319) 
(list 4160.135 869.7422) 
(list 4160.135 869.7525) 
(list 4160.135 869.7628) 
(list 4160.135 869.7731) 
(list 4160.135 869.7833) 
(list 4160.135 869.7936) 
(list 4160.135 869.8039) 
(list 4160.135 869.8142) 
(list 4160.135 869.8244) 
(list 4160.135 869.8347) 
(list 4160.135 869.845) 
(list 4160.135 869.8553) 
(list 4160.135 869.8656) 
(list 4160.135 869.8758) 
(list 4160.135 869.8861) 
(list 4160.135 869.8964) 
(list 4160.135 869.9067) 
(list 4160.135 869.9169) 
(list 4160.135 869.9272) 
(list 4160.135 869.9375) 
(list 4160.135 869.9478) 
(list 4160.135 869.9581) 
(list 4160.135 869.9683) 
(list 4160.135 869.9786) 
(list 4160.135 869.9889) 
(list 4160.135 869.9992) 
(list 4160.135 870.0094) 
(list 4160.135 870.0197) 
(list 4160.135 870.03) 
(list 4160 870.03)))
(apply 'command (append '("pline") coords '("c")))
(setq tap13 (ssadd (entlast) tap13))
(command "_mirror" (entlast) "" "4160,900" "4160,901" "No")
(setq tap13 (ssadd (entlast) tap13))
(setq coords (list 
(list 4160.4948 869.66) 
(list 4160.4859 869.66) 
(list 4160.4852 869.6703) 
(list 4160.4825 869.6806) 
(list 4160.4779 869.6908) 
(list 4160.4715 869.7011) 
(list 4160.4635 869.7114) 
(list 4160.4542 869.7217) 
(list 4160.4438 869.7319) 
(list 4160.4326 869.7422) 
(list 4160.421 869.7525) 
(list 4160.4094 869.7628) 
(list 4160.398 869.7731) 
(list 4160.3872 869.7833) 
(list 4160.3774 869.7936) 
(list 4160.3689 869.8039) 
(list 4160.3619 869.8142) 
(list 4160.3567 869.8244) 
(list 4160.3534 869.8347) 
(list 4160.3521 869.845) 
(list 4160.3529 869.8553) 
(list 4160.3559 869.8656) 
(list 4160.3608 869.8758) 
(list 4160.3677 869.8861) 
(list 4160.3762 869.8964) 
(list 4160.3861 869.9067) 
(list 4160.3972 869.9169) 
(list 4160.4091 869.9272) 
(list 4160.4214 869.9375) 
(list 4160.4338 869.9478) 
(list 4160.446 869.9581) 
(list 4160.4574 869.9683) 
(list 4160.4678 869.9786) 
(list 4160.4769 869.9889) 
(list 4160.4843 869.9992) 
(list 4160.4899 870.0094) 
(list 4160.4934 870.0197) 
(list 4160.4948 870.03) 
(list 4160.4948 870.03)))
(apply 'command (append '("pline") coords '("c")))
(setq tap13 (ssadd (entlast) tap13))
(command "_mirror" (entlast) "" "4160,900" "4160,901" "No")
(setq tap13 (ssadd (entlast) tap13))
(setq coords (list 
(list 4161.096 869.66) 
(list 4160.4948 869.66) 
(list 4160.4948 869.6703) 
(list 4160.4948 869.6806) 
(list 4160.4948 869.6908) 
(list 4160.4948 869.7011) 
(list 4160.4948 869.7114) 
(list 4160.4948 869.7217) 
(list 4160.4948 869.7319) 
(list 4160.4948 869.7422) 
(list 4160.4948 869.7525) 
(list 4160.4948 869.7628) 
(list 4160.4948 869.7731) 
(list 4160.4948 869.7833) 
(list 4160.4948 869.7936) 
(list 4160.4948 869.8039) 
(list 4160.4948 869.8142) 
(list 4160.4948 869.8244) 
(list 4160.4948 869.8347) 
(list 4160.4948 869.845) 
(list 4160.4948 869.8553) 
(list 4160.4948 869.8656) 
(list 4160.4948 869.8758) 
(list 4160.4948 869.8861) 
(list 4160.4948 869.8964) 
(list 4160.4948 869.9067) 
(list 4160.4948 869.9169) 
(list 4160.4948 869.9272) 
(list 4160.4948 869.9375) 
(list 4160.4948 869.9478) 
(list 4160.4948 869.9581) 
(list 4160.4948 869.9683) 
(list 4160.4948 869.9786) 
(list 4160.4948 869.9889) 
(list 4160.4948 869.9992) 
(list 4160.4948 870.0094) 
(list 4160.4948 870.0197) 
(list 4160.4948 870.03) 
(list 4161.096 870.03)))
(apply 'command (append '("pline") coords '("c")))
(setq tap13 (ssadd (entlast) tap13))
(command "_mirror" (entlast) "" "4160,900" "4160,901" "No")
(setq tap13 (ssadd (entlast) tap13))
(setq coords (list 
(list 4160 870.03) 
(list 4160.135 870.03) 
(list 4160.135 870.0403) 
(list 4160.135 870.0506) 
(list 4160.135 870.0608) 
(list 4160.135 870.0711) 
(list 4160.135 870.0814) 
(list 4160.135 870.0917) 
(list 4160.135 870.1019) 
(list 4160.135 870.1122) 
(list 4160.135 870.1225) 
(list 4160.135 870.1328) 
(list 4160.135 870.1431) 
(list 4160.135 870.1533) 
(list 4160.135 870.1636) 
(list 4160.135 870.1739) 
(list 4160.135 870.1842) 
(list 4160.135 870.1944) 
(list 4160.135 870.2047) 
(list 4160.135 870.215) 
(list 4160.135 870.2253) 
(list 4160.135 870.2356) 
(list 4160.135 870.2458) 
(list 4160.135 870.2561) 
(list 4160.135 870.2664) 
(list 4160.135 870.2767) 
(list 4160.135 870.2869) 
(list 4160.135 870.2972) 
(list 4160.135 870.3075) 
(list 4160.135 870.3178) 
(list 4160.135 870.3281) 
(list 4160.135 870.3383) 
(list 4160.135 870.3486) 
(list 4160.135 870.3589) 
(list 4160.135 870.3692) 
(list 4160.135 870.3794) 
(list 4160.135 870.3897) 
(list 4160.135 870.4) 
(list 4160 870.4)))
(apply 'command (append '("pline") coords '("c")))
(setq tap13 (ssadd (entlast) tap13))
(command "_mirror" (entlast) "" "4160,900" "4160,901" "No")
(setq tap13 (ssadd (entlast) tap13))
(setq coords (list 
(list 4160.5037 870.03) 
(list 4160.4948 870.03) 
(list 4160.4939 870.0403) 
(list 4160.4909 870.0506) 
(list 4160.4856 870.0608) 
(list 4160.4784 870.0711) 
(list 4160.4695 870.0814) 
(list 4160.459 870.0917) 
(list 4160.4473 870.1019) 
(list 4160.4348 870.1122) 
(list 4160.4218 870.1225) 
(list 4160.4087 870.1328) 
(list 4160.3959 870.1431) 
(list 4160.3839 870.1533) 
(list 4160.3729 870.1636) 
(list 4160.3634 870.1739) 
(list 4160.3556 870.1842) 
(list 4160.3497 870.1944) 
(list 4160.3461 870.2047) 
(list 4160.3447 870.215) 
(list 4160.3457 870.2253) 
(list 4160.349 870.2356) 
(list 4160.3545 870.2458) 
(list 4160.3622 870.2561) 
(list 4160.3717 870.2664) 
(list 4160.3828 870.2767) 
(list 4160.3951 870.2869) 
(list 4160.4084 870.2972) 
(list 4160.4222 870.3075) 
(list 4160.436 870.3178) 
(list 4160.4495 870.3281) 
(list 4160.4622 870.3383) 
(list 4160.4738 870.3486) 
(list 4160.4839 870.3589) 
(list 4160.4921 870.3692) 
(list 4160.4983 870.3794) 
(list 4160.5022 870.3897) 
(list 4160.5037 870.4) 
(list 4160.5037 870.4)))
(apply 'command (append '("pline") coords '("c")))
(setq tap13 (ssadd (entlast) tap13))
(command "_mirror" (entlast) "" "4160,900" "4160,901" "No")
(setq tap13 (ssadd (entlast) tap13))
(setq coords (list 
(list 4161.096 870.03) 
(list 4160.5037 870.03) 
(list 4160.5037 870.0403) 
(list 4160.5037 870.0506) 
(list 4160.5037 870.0608) 
(list 4160.5037 870.0711) 
(list 4160.5037 870.0814) 
(list 4160.5037 870.0917) 
(list 4160.5037 870.1019) 
(list 4160.5037 870.1122) 
(list 4160.5037 870.1225) 
(list 4160.5037 870.1328) 
(list 4160.5037 870.1431) 
(list 4160.5037 870.1533) 
(list 4160.5037 870.1636) 
(list 4160.5037 870.1739) 
(list 4160.5037 870.1842) 
(list 4160.5037 870.1944) 
(list 4160.5037 870.2047) 
(list 4160.5037 870.215) 
(list 4160.5037 870.2253) 
(list 4160.5037 870.2356) 
(list 4160.5037 870.2458) 
(list 4160.5037 870.2561) 
(list 4160.5037 870.2664) 
(list 4160.5037 870.2767) 
(list 4160.5037 870.2869) 
(list 4160.5037 870.2972) 
(list 4160.5037 870.3075) 
(list 4160.5037 870.3178) 
(list 4160.5037 870.3281) 
(list 4160.5037 870.3383) 
(list 4160.5037 870.3486) 
(list 4160.5037 870.3589) 
(list 4160.5037 870.3692) 
(list 4160.5037 870.3794) 
(list 4160.5037 870.3897) 
(list 4160.5037 870.4) 
(list 4161.096 870.4)))
(apply 'command (append '("pline") coords '("c")))
(setq tap13 (ssadd (entlast) tap13))
(command "_mirror" (entlast) "" "4160,900" "4160,901" "No")
(setq tap13 (ssadd (entlast) tap13))
(setq coords (list 
(list 4160 870.4) 
(list 4160.135 870.4) 
(list 4160.135 870.4103) 
(list 4160.135 870.4206) 
(list 4160.135 870.4308) 
(list 4160.135 870.4411) 
(list 4160.135 870.4514) 
(list 4160.135 870.4617) 
(list 4160.135 870.4719) 
(list 4160.135 870.4822) 
(list 4160.135 870.4925) 
(list 4160.135 870.5028) 
(list 4160.135 870.5131) 
(list 4160.135 870.5233) 
(list 4160.135 870.5336) 
(list 4160.135 870.5439) 
(list 4160.135 870.5542) 
(list 4160.135 870.5644) 
(list 4160.135 870.5747) 
(list 4160.135 870.585) 
(list 4160.135 870.5953) 
(list 4160.135 870.6056) 
(list 4160.135 870.6158) 
(list 4160.135 870.6261) 
(list 4160.135 870.6364) 
(list 4160.135 870.6467) 
(list 4160.135 870.6569) 
(list 4160.135 870.6672) 
(list 4160.135 870.6775) 
(list 4160.135 870.6878) 
(list 4160.135 870.6981) 
(list 4160.135 870.7083) 
(list 4160.135 870.7186) 
(list 4160.135 870.7289) 
(list 4160.135 870.7392) 
(list 4160.135 870.7494) 
(list 4160.135 870.7597) 
(list 4160.135 870.77) 
(list 4160 870.77)))
(apply 'command (append '("pline") coords '("c")))
(setq tap13 (ssadd (entlast) tap13))
(command "_mirror" (entlast) "" "4160,900" "4160,901" "No")
(setq tap13 (ssadd (entlast) tap13))
(setq coords (list 
(list 4160.5125 870.4) 
(list 4160.5037 870.4) 
(list 4160.5027 870.4103) 
(list 4160.4992 870.4206) 
(list 4160.4934 870.4308) 
(list 4160.4854 870.4411) 
(list 4160.4754 870.4514) 
(list 4160.4638 870.4617) 
(list 4160.4508 870.4719) 
(list 4160.4369 870.4822) 
(list 4160.4225 870.4925) 
(list 4160.408 870.5028) 
(list 4160.3939 870.5131) 
(list 4160.3806 870.5233) 
(list 4160.3684 870.5336) 
(list 4160.3579 870.5439) 
(list 4160.3493 870.5542) 
(list 4160.3428 870.5644) 
(list 4160.3388 870.5747) 
(list 4160.3373 870.585) 
(list 4160.3384 870.5953) 
(list 4160.3421 870.6056) 
(list 4160.3482 870.6158) 
(list 4160.3567 870.6261) 
(list 4160.3672 870.6364) 
(list 4160.3794 870.6467) 
(list 4160.3931 870.6569) 
(list 4160.4077 870.6672) 
(list 4160.4229 870.6775) 
(list 4160.4381 870.6878) 
(list 4160.453 870.6981) 
(list 4160.467 870.7083) 
(list 4160.4797 870.7186) 
(list 4160.4908 870.7289) 
(list 4160.4999 870.7392) 
(list 4160.5067 870.7494) 
(list 4160.5109 870.7597) 
(list 4160.5125 870.77) 
(list 4160.5125 870.77)))
(apply 'command (append '("pline") coords '("c")))
(setq tap13 (ssadd (entlast) tap13))
(command "_mirror" (entlast) "" "4160,900" "4160,901" "No")
(setq tap13 (ssadd (entlast) tap13))
(setq coords (list 
(list 4161.096 870.4) 
(list 4160.5125 870.4) 
(list 4160.5125 870.4103) 
(list 4160.5125 870.4206) 
(list 4160.5125 870.4308) 
(list 4160.5125 870.4411) 
(list 4160.5125 870.4514) 
(list 4160.5125 870.4617) 
(list 4160.5125 870.4719) 
(list 4160.5125 870.4822) 
(list 4160.5125 870.4925) 
(list 4160.5125 870.5028) 
(list 4160.5125 870.5131) 
(list 4160.5125 870.5233) 
(list 4160.5125 870.5336) 
(list 4160.5125 870.5439) 
(list 4160.5125 870.5542) 
(list 4160.5125 870.5644) 
(list 4160.5125 870.5747) 
(list 4160.5125 870.585) 
(list 4160.5125 870.5953) 
(list 4160.5125 870.6056) 
(list 4160.5125 870.6158) 
(list 4160.5125 870.6261) 
(list 4160.5125 870.6364) 
(list 4160.5125 870.6467) 
(list 4160.5125 870.6569) 
(list 4160.5125 870.6672) 
(list 4160.5125 870.6775) 
(list 4160.5125 870.6878) 
(list 4160.5125 870.6981) 
(list 4160.5125 870.7083) 
(list 4160.5125 870.7186) 
(list 4160.5125 870.7289) 
(list 4160.5125 870.7392) 
(list 4160.5125 870.7494) 
(list 4160.5125 870.7597) 
(list 4160.5125 870.77) 
(list 4161.096 870.77)))
(apply 'command (append '("pline") coords '("c")))
(setq tap13 (ssadd (entlast) tap13))
(command "_mirror" (entlast) "" "4160,900" "4160,901" "No")
(setq tap13 (ssadd (entlast) tap13))
(setq coords (list 
(list 4160 870.77) 
(list 4160.135 870.77) 
(list 4160.135 870.7803) 
(list 4160.135 870.7906) 
(list 4160.135 870.8008) 
(list 4160.135 870.8111) 
(list 4160.135 870.8214) 
(list 4160.135 870.8317) 
(list 4160.135 870.8419) 
(list 4160.135 870.8522) 
(list 4160.135 870.8625) 
(list 4160.135 870.8728) 
(list 4160.135 870.8831) 
(list 4160.135 870.8933) 
(list 4160.135 870.9036) 
(list 4160.135 870.9139) 
(list 4160.135 870.9242) 
(list 4160.135 870.9344) 
(list 4160.135 870.9447) 
(list 4160.135 870.955) 
(list 4160.135 870.9653) 
(list 4160.135 870.9756) 
(list 4160.135 870.9858) 
(list 4160.135 870.9961) 
(list 4160.135 871.0064) 
(list 4160.135 871.0167) 
(list 4160.135 871.0269) 
(list 4160.135 871.0372) 
(list 4160.135 871.0475) 
(list 4160.135 871.0578) 
(list 4160.135 871.0681) 
(list 4160.135 871.0783) 
(list 4160.135 871.0886) 
(list 4160.135 871.0989) 
(list 4160.135 871.1092) 
(list 4160.135 871.1194) 
(list 4160.135 871.1297) 
(list 4160.135 871.14) 
(list 4160 871.14)))
(apply 'command (append '("pline") coords '("c")))
(setq tap13 (ssadd (entlast) tap13))
(command "_mirror" (entlast) "" "4160,900" "4160,901" "No")
(setq tap13 (ssadd (entlast) tap13))
(setq coords (list 
(list 4160.5214 870.77) 
(list 4160.5125 870.77) 
(list 4160.5114 870.7803) 
(list 4160.5076 870.7906) 
(list 4160.5012 870.8008) 
(list 4160.4924 870.8111) 
(list 4160.4814 870.8214) 
(list 4160.4686 870.8317) 
(list 4160.4543 870.8419) 
(list 4160.4391 870.8522) 
(list 4160.4232 870.8625) 
(list 4160.4073 870.8728) 
(list 4160.3918 870.8831) 
(list 4160.3772 870.8933) 
(list 4160.3639 870.9036) 
(list 4160.3524 870.9139) 
(list 4160.343 870.9242) 
(list 4160.3359 870.9344) 
(list 4160.3315 870.9447) 
(list 4160.3299 870.955) 
(list 4160.3311 870.9653) 
(list 4160.3352 870.9756) 
(list 4160.3419 870.9858) 
(list 4160.3512 870.9961) 
(list 4160.3627 871.0064) 
(list 4160.3761 871.0167) 
(list 4160.391 871.0269) 
(list 4160.407 871.0372) 
(list 4160.4236 871.0475) 
(list 4160.4403 871.0578) 
(list 4160.4565 871.0681) 
(list 4160.4718 871.0783) 
(list 4160.4857 871.0886) 
(list 4160.4978 871.0989) 
(list 4160.5077 871.1092) 
(list 4160.515 871.1194) 
(list 4160.5197 871.1297) 
(list 4160.5214 871.14) 
(list 4160.5214 871.14)))
(apply 'command (append '("pline") coords '("c")))
(setq tap13 (ssadd (entlast) tap13))
(command "_mirror" (entlast) "" "4160,900" "4160,901" "No")
(setq tap13 (ssadd (entlast) tap13))
(setq coords (list 
(list 4161.096 870.77) 
(list 4160.5214 870.77) 
(list 4160.5214 870.7803) 
(list 4160.5214 870.7906) 
(list 4160.5214 870.8008) 
(list 4160.5214 870.8111) 
(list 4160.5214 870.8214) 
(list 4160.5214 870.8317) 
(list 4160.5214 870.8419) 
(list 4160.5214 870.8522) 
(list 4160.5214 870.8625) 
(list 4160.5214 870.8728) 
(list 4160.5214 870.8831) 
(list 4160.5214 870.8933) 
(list 4160.5214 870.9036) 
(list 4160.5214 870.9139) 
(list 4160.5214 870.9242) 
(list 4160.5214 870.9344) 
(list 4160.5214 870.9447) 
(list 4160.5214 870.955) 
(list 4160.5214 870.9653) 
(list 4160.5214 870.9756) 
(list 4160.5214 870.9858) 
(list 4160.5214 870.9961) 
(list 4160.5214 871.0064) 
(list 4160.5214 871.0167) 
(list 4160.5214 871.0269) 
(list 4160.5214 871.0372) 
(list 4160.5214 871.0475) 
(list 4160.5214 871.0578) 
(list 4160.5214 871.0681) 
(list 4160.5214 871.0783) 
(list 4160.5214 871.0886) 
(list 4160.5214 871.0989) 
(list 4160.5214 871.1092) 
(list 4160.5214 871.1194) 
(list 4160.5214 871.1297) 
(list 4160.5214 871.14) 
(list 4161.096 871.14)))
(apply 'command (append '("pline") coords '("c")))
(setq tap13 (ssadd (entlast) tap13))
(command "_mirror" (entlast) "" "4160,900" "4160,901" "No")
(setq tap13 (ssadd (entlast) tap13))
(setq coords (list 
(list 4160 871.14) 
(list 4160.135 871.14) 
(list 4160.135 871.1503) 
(list 4160.135 871.1606) 
(list 4160.135 871.1708) 
(list 4160.135 871.1811) 
(list 4160.135 871.1914) 
(list 4160.135 871.2017) 
(list 4160.135 871.2119) 
(list 4160.135 871.2222) 
(list 4160.135 871.2325) 
(list 4160.135 871.2428) 
(list 4160.135 871.2531) 
(list 4160.135 871.2633) 
(list 4160.135 871.2736) 
(list 4160.135 871.2839) 
(list 4160.135 871.2942) 
(list 4160.135 871.3044) 
(list 4160.135 871.3147) 
(list 4160.135 871.325) 
(list 4160.135 871.3353) 
(list 4160.135 871.3456) 
(list 4160.135 871.3558) 
(list 4160.135 871.3661) 
(list 4160.135 871.3764) 
(list 4160.135 871.3867) 
(list 4160.135 871.3969) 
(list 4160.135 871.4072) 
(list 4160.135 871.4175) 
(list 4160.135 871.4278) 
(list 4160.135 871.4381) 
(list 4160.135 871.4483) 
(list 4160.135 871.4586) 
(list 4160.135 871.4689) 
(list 4160.135 871.4792) 
(list 4160.135 871.4894) 
(list 4160.135 871.4997) 
(list 4160.135 871.51) 
(list 4160 871.51)))
(apply 'command (append '("pline") coords '("c")))
(setq tap13 (ssadd (entlast) tap13))
(command "_mirror" (entlast) "" "4160,900" "4160,901" "No")
(setq tap13 (ssadd (entlast) tap13))
(setq coords (list 
(list 4160.5303 871.14) 
(list 4160.5214 871.14) 
(list 4160.5202 871.1503) 
(list 4160.516 871.1606) 
(list 4160.509 871.1708) 
(list 4160.4993 871.1811) 
(list 4160.4874 871.1914) 
(list 4160.4734 871.2017) 
(list 4160.4579 871.2119) 
(list 4160.4412 871.2222) 
(list 4160.424 871.2325) 
(list 4160.4067 871.2428) 
(list 4160.3898 871.2531) 
(list 4160.3739 871.2633) 
(list 4160.3594 871.2736) 
(list 4160.3469 871.2839) 
(list 4160.3366 871.2942) 
(list 4160.329 871.3044) 
(list 4160.3242 871.3147) 
(list 4160.3225 871.325) 
(list 4160.3238 871.3353) 
(list 4160.3282 871.3456) 
(list 4160.3356 871.3558) 
(list 4160.3457 871.3661) 
(list 4160.3582 871.3764) 
(list 4160.3728 871.3867) 
(list 4160.389 871.3969) 
(list 4160.4064 871.4072) 
(list 4160.4244 871.4175) 
(list 4160.4424 871.4278) 
(list 4160.46 871.4381) 
(list 4160.4766 871.4483) 
(list 4160.4917 871.4586) 
(list 4160.5048 871.4689) 
(list 4160.5155 871.4792) 
(list 4160.5234 871.4894) 
(list 4160.5284 871.4997) 
(list 4160.5303 871.51) 
(list 4160.5303 871.51)))
(apply 'command (append '("pline") coords '("c")))
(setq tap13 (ssadd (entlast) tap13))
(command "_mirror" (entlast) "" "4160,900" "4160,901" "No")
(setq tap13 (ssadd (entlast) tap13))
(setq coords (list 
(list 4161.096 871.14) 
(list 4160.5303 871.14) 
(list 4160.5303 871.1503) 
(list 4160.5303 871.1606) 
(list 4160.5303 871.1708) 
(list 4160.5303 871.1811) 
(list 4160.5303 871.1914) 
(list 4160.5303 871.2017) 
(list 4160.5303 871.2119) 
(list 4160.5303 871.2222) 
(list 4160.5303 871.2325) 
(list 4160.5303 871.2428) 
(list 4160.5303 871.2531) 
(list 4160.5303 871.2633) 
(list 4160.5303 871.2736) 
(list 4160.5303 871.2839) 
(list 4160.5303 871.2942) 
(list 4160.5303 871.3044) 
(list 4160.5303 871.3147) 
(list 4160.5303 871.325) 
(list 4160.5303 871.3353) 
(list 4160.5303 871.3456) 
(list 4160.5303 871.3558) 
(list 4160.5303 871.3661) 
(list 4160.5303 871.3764) 
(list 4160.5303 871.3867) 
(list 4160.5303 871.3969) 
(list 4160.5303 871.4072) 
(list 4160.5303 871.4175) 
(list 4160.5303 871.4278) 
(list 4160.5303 871.4381) 
(list 4160.5303 871.4483) 
(list 4160.5303 871.4586) 
(list 4160.5303 871.4689) 
(list 4160.5303 871.4792) 
(list 4160.5303 871.4894) 
(list 4160.5303 871.4997) 
(list 4160.5303 871.51) 
(list 4161.096 871.51)))
(apply 'command (append '("pline") coords '("c")))
(setq tap13 (ssadd (entlast) tap13))
(command "_mirror" (entlast) "" "4160,900" "4160,901" "No")
(setq tap13 (ssadd (entlast) tap13))
(setq coords (list 
(list 4160 871.51) 
(list 4160.135 871.51) 
(list 4160.135 871.5203) 
(list 4160.135 871.5306) 
(list 4160.135 871.5408) 
(list 4160.135 871.5511) 
(list 4160.135 871.5614) 
(list 4160.135 871.5717) 
(list 4160.135 871.5819) 
(list 4160.135 871.5922) 
(list 4160.135 871.6025) 
(list 4160.135 871.6128) 
(list 4160.135 871.6231) 
(list 4160.135 871.6333) 
(list 4160.135 871.6436) 
(list 4160.135 871.6539) 
(list 4160.135 871.6642) 
(list 4160.135 871.6744) 
(list 4160.135 871.6847) 
(list 4160.135 871.695) 
(list 4160.135 871.7053) 
(list 4160.135 871.7156) 
(list 4160.135 871.7258) 
(list 4160.135 871.7361) 
(list 4160.135 871.7464) 
(list 4160.135 871.7567) 
(list 4160.135 871.7669) 
(list 4160.135 871.7772) 
(list 4160.135 871.7875) 
(list 4160.135 871.7978) 
(list 4160.135 871.8081) 
(list 4160.135 871.8183) 
(list 4160.135 871.8286) 
(list 4160.135 871.8389) 
(list 4160.135 871.8492) 
(list 4160.135 871.8594) 
(list 4160.135 871.8697) 
(list 4160.135 871.88) 
(list 4160 871.88)))
(apply 'command (append '("pline") coords '("c")))
(setq tap13 (ssadd (entlast) tap13))
(command "_mirror" (entlast) "" "4160,900" "4160,901" "No")
(setq tap13 (ssadd (entlast) tap13))
(setq coords (list 
(list 4160.5391 871.51) 
(list 4160.5303 871.51) 
(list 4160.5289 871.5203) 
(list 4160.5244 871.5306) 
(list 4160.5167 871.5408) 
(list 4160.5063 871.5511) 
(list 4160.4933 871.5614) 
(list 4160.4782 871.5717) 
(list 4160.4614 871.5819) 
(list 4160.4434 871.5922) 
(list 4160.4247 871.6025) 
(list 4160.406 871.6128) 
(list 4160.3877 871.6231) 
(list 4160.3706 871.6333) 
(list 4160.3549 871.6436) 
(list 4160.3414 871.6539) 
(list 4160.3303 871.6642) 
(list 4160.3221 871.6744) 
(list 4160.317 871.6847) 
(list 4160.3151 871.695) 
(list 4160.3166 871.7053) 
(list 4160.3213 871.7156) 
(list 4160.3293 871.7258) 
(list 4160.3402 871.7361) 
(list 4160.3537 871.7464) 
(list 4160.3694 871.7567) 
(list 4160.3869 871.7669) 
(list 4160.4057 871.7772) 
(list 4160.4251 871.7875) 
(list 4160.4446 871.7978) 
(list 4160.4635 871.8081) 
(list 4160.4814 871.8183) 
(list 4160.4976 871.8286) 
(list 4160.5117 871.8389) 
(list 4160.5232 871.8492) 
(list 4160.5318 871.8594) 
(list 4160.5372 871.8697) 
(list 4160.5391 871.88) 
(list 4160.5391 871.88)))
(apply 'command (append '("pline") coords '("c")))
(setq tap13 (ssadd (entlast) tap13))
(command "_mirror" (entlast) "" "4160,900" "4160,901" "No")
(setq tap13 (ssadd (entlast) tap13))
(setq coords (list 
(list 4161.096 871.51) 
(list 4160.5391 871.51) 
(list 4160.5391 871.5203) 
(list 4160.5391 871.5306) 
(list 4160.5391 871.5408) 
(list 4160.5391 871.5511) 
(list 4160.5391 871.5614) 
(list 4160.5391 871.5717) 
(list 4160.5391 871.5819) 
(list 4160.5391 871.5922) 
(list 4160.5391 871.6025) 
(list 4160.5391 871.6128) 
(list 4160.5391 871.6231) 
(list 4160.5391 871.6333) 
(list 4160.5391 871.6436) 
(list 4160.5391 871.6539) 
(list 4160.5391 871.6642) 
(list 4160.5391 871.6744) 
(list 4160.5391 871.6847) 
(list 4160.5391 871.695) 
(list 4160.5391 871.7053) 
(list 4160.5391 871.7156) 
(list 4160.5391 871.7258) 
(list 4160.5391 871.7361) 
(list 4160.5391 871.7464) 
(list 4160.5391 871.7567) 
(list 4160.5391 871.7669) 
(list 4160.5391 871.7772) 
(list 4160.5391 871.7875) 
(list 4160.5391 871.7978) 
(list 4160.5391 871.8081) 
(list 4160.5391 871.8183) 
(list 4160.5391 871.8286) 
(list 4160.5391 871.8389) 
(list 4160.5391 871.8492) 
(list 4160.5391 871.8594) 
(list 4160.5391 871.8697) 
(list 4160.5391 871.88) 
(list 4161.096 871.88)))
(apply 'command (append '("pline") coords '("c")))
(setq tap13 (ssadd (entlast) tap13))
(command "_mirror" (entlast) "" "4160,900" "4160,901" "No")
(setq tap13 (ssadd (entlast) tap13))
(setq coords (list 
(list 4160 871.88) 
(list 4160.135 871.88) 
(list 4160.135 871.8903) 
(list 4160.135 871.9006) 
(list 4160.135 871.9108) 
(list 4160.135 871.9211) 
(list 4160.135 871.9314) 
(list 4160.135 871.9417) 
(list 4160.135 871.9519) 
(list 4160.135 871.9622) 
(list 4160.135 871.9725) 
(list 4160.135 871.9828) 
(list 4160.135 871.9931) 
(list 4160.135 872.0033) 
(list 4160.135 872.0136) 
(list 4160.135 872.0239) 
(list 4160.135 872.0342) 
(list 4160.135 872.0444) 
(list 4160.135 872.0547) 
(list 4160.135 872.065) 
(list 4160.135 872.0753) 
(list 4160.135 872.0856) 
(list 4160.135 872.0958) 
(list 4160.135 872.1061) 
(list 4160.135 872.1164) 
(list 4160.135 872.1267) 
(list 4160.135 872.1369) 
(list 4160.135 872.1472) 
(list 4160.135 872.1575) 
(list 4160.135 872.1678) 
(list 4160.135 872.1781) 
(list 4160.135 872.1883) 
(list 4160.135 872.1986) 
(list 4160.135 872.2089) 
(list 4160.135 872.2192) 
(list 4160.135 872.2294) 
(list 4160.135 872.2397) 
(list 4160.135 872.25) 
(list 4160 872.25)))
(apply 'command (append '("pline") coords '("c")))
(setq tap13 (ssadd (entlast) tap13))
(command "_mirror" (entlast) "" "4160,900" "4160,901" "No")
(setq tap13 (ssadd (entlast) tap13))
(setq coords (list 
(list 4160.548 871.88) 
(list 4160.5391 871.88) 
(list 4160.5376 871.8903) 
(list 4160.5327 871.9006) 
(list 4160.5245 871.9108) 
(list 4160.5133 871.9211) 
(list 4160.4993 871.9314) 
(list 4160.483 871.9417) 
(list 4160.4649 871.9519) 
(list 4160.4455 871.9622) 
(list 4160.4254 871.9725) 
(list 4160.4053 871.9828) 
(list 4160.3857 871.9931) 
(list 4160.3672 872.0033) 
(list 4160.3505 872.0136) 
(list 4160.3359 872.0239) 
(list 4160.324 872.0342) 
(list 4160.3152 872.0444) 
(list 4160.3097 872.0547) 
(list 4160.3077 872.065) 
(list 4160.3093 872.0753) 
(list 4160.3144 872.0856) 
(list 4160.323 872.0958) 
(list 4160.3347 872.1061) 
(list 4160.3492 872.1164) 
(list 4160.3661 872.1267) 
(list 4160.3849 872.1369) 
(list 4160.405 872.1472) 
(list 4160.4258 872.1575) 
(list 4160.4467 872.1678) 
(list 4160.467 872.1781) 
(list 4160.4862 872.1883) 
(list 4160.5036 872.1986) 
(list 4160.5187 872.2089) 
(list 4160.531 872.2192) 
(list 4160.5402 872.2294) 
(list 4160.5459 872.2397) 
(list 4160.548 872.25) 
(list 4160.548 872.25)))
(apply 'command (append '("pline") coords '("c")))
(setq tap13 (ssadd (entlast) tap13))
(command "_mirror" (entlast) "" "4160,900" "4160,901" "No")
(setq tap13 (ssadd (entlast) tap13))
(setq coords (list 
(list 4161.096 871.88) 
(list 4160.548 871.88) 
(list 4160.548 871.8903) 
(list 4160.548 871.9006) 
(list 4160.548 871.9108) 
(list 4160.548 871.9211) 
(list 4160.548 871.9314) 
(list 4160.548 871.9417) 
(list 4160.548 871.9519) 
(list 4160.548 871.9622) 
(list 4160.548 871.9725) 
(list 4160.548 871.9828) 
(list 4160.548 871.9931) 
(list 4160.548 872.0033) 
(list 4160.548 872.0136) 
(list 4160.548 872.0239) 
(list 4160.548 872.0342) 
(list 4160.548 872.0444) 
(list 4160.548 872.0547) 
(list 4160.548 872.065) 
(list 4160.548 872.0753) 
(list 4160.548 872.0856) 
(list 4160.548 872.0958) 
(list 4160.548 872.1061) 
(list 4160.548 872.1164) 
(list 4160.548 872.1267) 
(list 4160.548 872.1369) 
(list 4160.548 872.1472) 
(list 4160.548 872.1575) 
(list 4160.548 872.1678) 
(list 4160.548 872.1781) 
(list 4160.548 872.1883) 
(list 4160.548 872.1986) 
(list 4160.548 872.2089) 
(list 4160.548 872.2192) 
(list 4160.548 872.2294) 
(list 4160.548 872.2397) 
(list 4160.548 872.25) 
(list 4161.096 872.25)))
(apply 'command (append '("pline") coords '("c")))
(setq tap13 (ssadd (entlast) tap13))
(command "_mirror" (entlast) "" "4160,900" "4160,901" "No")
(setq tap13 (ssadd (entlast) tap13))
(command "_block" "blktap13" "4160,900" tap13 "")
(command "_insert" "blktap13" "4160,900" "1" "1" "0")
(command "_insert" "blktap13" "4160,900" "1" "1" "180")
(setq uc13 nil)
(setq uc13 (ssadd))
(setq coords (list 
(list 0 -0.185) 
(list 0.135 -0.185) 
(list 0.135 -0.17472) 
(list 0.135 -0.16444) 
(list 0.135 -0.15417) 
(list 0.135 -0.14389) 
(list 0.135 -0.13361) 
(list 0.135 -0.12333) 
(list 0.135 -0.11306) 
(list 0.135 -0.10278) 
(list 0.135 -0.0925) 
(list 0.135 -0.082222) 
(list 0.135 -0.071944) 
(list 0.135 -0.061667) 
(list 0.135 -0.051389) 
(list 0.135 -0.041111) 
(list 0.135 -0.030833) 
(list 0.135 -0.020556) 
(list 0.135 -0.010278) 
(list 0.135 0) 
(list 0.135 0.010278) 
(list 0.135 0.020556) 
(list 0.135 0.030833) 
(list 0.135 0.041111) 
(list 0.135 0.051389) 
(list 0.135 0.061667) 
(list 0.135 0.071944) 
(list 0.135 0.082222) 
(list 0.135 0.0925) 
(list 0.135 0.10278) 
(list 0.135 0.11306) 
(list 0.135 0.12333) 
(list 0.135 0.13361) 
(list 0.135 0.14389) 
(list 0.135 0.15417) 
(list 0.135 0.16444) 
(list 0.135 0.17472) 
(list 0.135 0.185) 
(list 0 0.185)))
(apply 'command (append '("pline") coords '("c")))
(setq uc13 (ssadd (entlast) uc13))
(setq coords (list 
(list 1.096 -0.185) 
(list 0.548 -0.185) 
(list 0.54615 -0.17472) 
(list 0.54064 -0.16444) 
(list 0.53165 -0.15417) 
(list 0.51946 -0.14389) 
(list 0.50442 -0.13361) 
(list 0.487 -0.12333) 
(list 0.46773 -0.11306) 
(list 0.44718 -0.10278) 
(list 0.426 -0.0925) 
(list 0.40481 -0.082222) 
(list 0.38427 -0.071944) 
(list 0.365 -0.061667) 
(list 0.34758 -0.051389) 
(list 0.33254 -0.041111) 
(list 0.32034 -0.030833) 
(list 0.31136 -0.020556) 
(list 0.30585 -0.010278) 
(list 0.304 0) 
(list 0.30585 0.010278) 
(list 0.31136 0.020556) 
(list 0.32034 0.030833) 
(list 0.33254 0.041111) 
(list 0.34758 0.051389) 
(list 0.365 0.061667) 
(list 0.38427 0.071944) 
(list 0.40481 0.082222) 
(list 0.426 0.0925) 
(list 0.44718 0.10278) 
(list 0.46773 0.11306) 
(list 0.487 0.12333) 
(list 0.50442 0.13361) 
(list 0.51946 0.14389) 
(list 0.53165 0.15417) 
(list 0.54064 0.16444) 
(list 0.54615 0.17472) 
(list 0.548 0.185) 
(list 1.096 0.185)))
(apply 'command (append '("pline") coords '("c")))
(setq uc13 (ssadd (entlast) uc13))
(command "_block" "blkuc13" "0,0.185" uc13 "")
(command "_insert" "blkuc13" "4160,872.62" "1" "1" "0")
(command "_insert" "blkuc13" "4160,872.25" "1" "1" "180")
(command "_insert" "blkuc13" "4160,872.99" "1" "1" "0")
(command "_insert" "blkuc13" "4160,872.62" "1" "1" "180")
(command "_insert" "blkuc13" "4160,873.36" "1" "1" "0")
(command "_insert" "blkuc13" "4160,872.99" "1" "1" "180")
(command "_insert" "blkuc13" "4160,873.73" "1" "1" "0")
(command "_insert" "blkuc13" "4160,873.36" "1" "1" "180")
(command "_insert" "blkuc13" "4160,874.1" "1" "1" "0")
(command "_insert" "blkuc13" "4160,873.73" "1" "1" "180")
(command "_insert" "blkuc13" "4160,874.47" "1" "1" "0")
(command "_insert" "blkuc13" "4160,874.1" "1" "1" "180")
(command "_insert" "blkuc13" "4160,874.84" "1" "1" "0")
(command "_insert" "blkuc13" "4160,874.47" "1" "1" "180")
(command "_insert" "blkuc13" "4160,875.21" "1" "1" "0")
(command "_insert" "blkuc13" "4160,874.84" "1" "1" "180")
(command "_insert" "blkuc13" "4160,875.58" "1" "1" "0")
(command "_insert" "blkuc13" "4160,875.21" "1" "1" "180")
(command "_insert" "blkuc13" "4160,875.95" "1" "1" "0")
(command "_insert" "blkuc13" "4160,875.58" "1" "1" "180")
(command "_insert" "blkuc13" "4160,876.32" "1" "1" "0")
(command "_insert" "blkuc13" "4160,875.95" "1" "1" "180")
(command "_insert" "blkuc13" "4160,876.69" "1" "1" "0")
(command "_insert" "blkuc13" "4160,876.32" "1" "1" "180")
(command "_insert" "blkuc13" "4160,877.06" "1" "1" "0")
(command "_insert" "blkuc13" "4160,876.69" "1" "1" "180")
(command "_insert" "blkuc13" "4160,877.43" "1" "1" "0")
(command "_insert" "blkuc13" "4160,877.06" "1" "1" "180")
(command "_insert" "blkuc13" "4160,877.8" "1" "1" "0")
(command "_insert" "blkuc13" "4160,877.43" "1" "1" "180")
(command "_insert" "blkuc13" "4160,878.17" "1" "1" "0")
(command "_insert" "blkuc13" "4160,877.8" "1" "1" "180")
(command "_insert" "blkuc13" "4160,878.54" "1" "1" "0")
(command "_insert" "blkuc13" "4160,878.17" "1" "1" "180")
(command "_insert" "blkuc13" "4160,878.91" "1" "1" "0")
(command "_insert" "blkuc13" "4160,878.54" "1" "1" "180")
(command "_insert" "blkuc13" "4160,879.28" "1" "1" "0")
(command "_insert" "blkuc13" "4160,878.91" "1" "1" "180")
(command "_insert" "blkuc13" "4160,879.65" "1" "1" "0")
(command "_insert" "blkuc13" "4160,879.28" "1" "1" "180")
(command "_insert" "blkuc13" "4160,880.02" "1" "1" "0")
(command "_insert" "blkuc13" "4160,879.65" "1" "1" "180")
(command "_insert" "blkuc13" "4160,880.39" "1" "1" "0")
(command "_insert" "blkuc13" "4160,880.02" "1" "1" "180")
(command "_insert" "blkuc13" "4160,880.76" "1" "1" "0")
(command "_insert" "blkuc13" "4160,880.39" "1" "1" "180")
(command "_insert" "blkuc13" "4160,881.13" "1" "1" "0")
(command "_insert" "blkuc13" "4160,880.76" "1" "1" "180")
(command "_insert" "blkuc13" "4160,881.5" "1" "1" "0")
(command "_insert" "blkuc13" "4160,881.13" "1" "1" "180")
(command "_insert" "blkuc13" "4160,881.87" "1" "1" "0")
(command "_insert" "blkuc13" "4160,881.5" "1" "1" "180")
(command "_insert" "blkuc13" "4160,882.24" "1" "1" "0")
(command "_insert" "blkuc13" "4160,881.87" "1" "1" "180")
(command "_insert" "blkuc13" "4160,882.61" "1" "1" "0")
(command "_insert" "blkuc13" "4160,882.24" "1" "1" "180")
(command "_insert" "blkuc13" "4160,882.98" "1" "1" "0")
(command "_insert" "blkuc13" "4160,882.61" "1" "1" "180")
(command "_insert" "blkuc13" "4160,883.35" "1" "1" "0")
(command "_insert" "blkuc13" "4160,882.98" "1" "1" "180")
(command "_insert" "blkuc13" "4160,883.72" "1" "1" "0")
(command "_insert" "blkuc13" "4160,883.35" "1" "1" "180")
(command "_insert" "blkuc13" "4160,884.09" "1" "1" "0")
(command "_insert" "blkuc13" "4160,883.72" "1" "1" "180")
(command "_insert" "blkuc13" "4160,884.46" "1" "1" "0")
(command "_insert" "blkuc13" "4160,884.09" "1" "1" "180")
(command "_insert" "blkuc13" "4160,884.83" "1" "1" "0")
(command "_insert" "blkuc13" "4160,884.46" "1" "1" "180")
(command "_insert" "blkuc13" "4160,885.2" "1" "1" "0")
(command "_insert" "blkuc13" "4160,884.83" "1" "1" "180")
(command "_insert" "blkuc13" "4160,885.57" "1" "1" "0")
(command "_insert" "blkuc13" "4160,885.2" "1" "1" "180")
(command "_insert" "blkuc13" "4160,885.94" "1" "1" "0")
(command "_insert" "blkuc13" "4160,885.57" "1" "1" "180")
(command "_insert" "blkuc13" "4160,886.31" "1" "1" "0")
(command "_insert" "blkuc13" "4160,885.94" "1" "1" "180")
(command "_insert" "blkuc13" "4160,886.68" "1" "1" "0")
(command "_insert" "blkuc13" "4160,886.31" "1" "1" "180")
(command "_insert" "blkuc13" "4160,887.05" "1" "1" "0")
(command "_insert" "blkuc13" "4160,886.68" "1" "1" "180")
(command "_insert" "blkuc13" "4160,887.42" "1" "1" "0")
(command "_insert" "blkuc13" "4160,887.05" "1" "1" "180")
(command "_insert" "blkuc13" "4160,887.79" "1" "1" "0")
(command "_insert" "blkuc13" "4160,887.42" "1" "1" "180")
(command "_insert" "blkuc13" "4160,888.16" "1" "1" "0")
(command "_insert" "blkuc13" "4160,887.79" "1" "1" "180")
(command "_insert" "blkuc13" "4160,888.53" "1" "1" "0")
(command "_insert" "blkuc13" "4160,888.16" "1" "1" "180")
(command "_insert" "blkuc13" "4160,888.9" "1" "1" "0")
(command "_insert" "blkuc13" "4160,888.53" "1" "1" "180")
(command "_insert" "blkuc13" "4160,889.27" "1" "1" "0")
(command "_insert" "blkuc13" "4160,888.9" "1" "1" "180")
(command "_insert" "blkuc13" "4160,889.64" "1" "1" "0")
(command "_insert" "blkuc13" "4160,889.27" "1" "1" "180")
(command "_insert" "blkuc13" "4160,890.01" "1" "1" "0")
(command "_insert" "blkuc13" "4160,889.64" "1" "1" "180")
(command "_insert" "blkuc13" "4160,890.38" "1" "1" "0")
(command "_insert" "blkuc13" "4160,890.01" "1" "1" "180")
(command "_insert" "blkuc13" "4160,890.75" "1" "1" "0")
(command "_insert" "blkuc13" "4160,890.38" "1" "1" "180")
(command "_insert" "blkuc13" "4160,891.12" "1" "1" "0")
(command "_insert" "blkuc13" "4160,890.75" "1" "1" "180")
(command "_insert" "blkuc13" "4160,891.49" "1" "1" "0")
(command "_insert" "blkuc13" "4160,891.12" "1" "1" "180")
(command "_insert" "blkuc13" "4160,891.86" "1" "1" "0")
(command "_insert" "blkuc13" "4160,891.49" "1" "1" "180")
(command "_insert" "blkuc13" "4160,892.23" "1" "1" "0")
(command "_insert" "blkuc13" "4160,891.86" "1" "1" "180")
(command "_insert" "blkuc13" "4160,892.6" "1" "1" "0")
(command "_insert" "blkuc13" "4160,892.23" "1" "1" "180")
(command "_insert" "blkuc13" "4160,892.97" "1" "1" "0")
(command "_insert" "blkuc13" "4160,892.6" "1" "1" "180")
(command "_insert" "blkuc13" "4160,893.34" "1" "1" "0")
(command "_insert" "blkuc13" "4160,892.97" "1" "1" "180")
(command "_insert" "blkuc13" "4160,893.71" "1" "1" "0")
(command "_insert" "blkuc13" "4160,893.34" "1" "1" "180")
(command "_insert" "blkuc13" "4160,894.08" "1" "1" "0")
(command "_insert" "blkuc13" "4160,893.71" "1" "1" "180")
(command "_insert" "blkuc13" "4160,894.45" "1" "1" "0")
(command "_insert" "blkuc13" "4160,894.08" "1" "1" "180")
(command "_insert" "blkuc13" "4160,894.82" "1" "1" "0")
(command "_insert" "blkuc13" "4160,894.45" "1" "1" "180")
(command "_insert" "blkuc13" "4160,895.19" "1" "1" "0")
(command "_insert" "blkuc13" "4160,894.82" "1" "1" "180")
(command "_insert" "blkuc13" "4160,895.56" "1" "1" "0")
(command "_insert" "blkuc13" "4160,895.19" "1" "1" "180")
(command "_insert" "blkuc13" "4160,895.93" "1" "1" "0")
(command "_insert" "blkuc13" "4160,895.56" "1" "1" "180")
(command "_insert" "blkuc13" "4160,896.3" "1" "1" "0")
(command "_insert" "blkuc13" "4160,895.93" "1" "1" "180")
(command "_insert" "blkuc13" "4160,896.67" "1" "1" "0")
(command "_insert" "blkuc13" "4160,896.3" "1" "1" "180")
(command "_insert" "blkuc13" "4160,897.04" "1" "1" "0")
(command "_insert" "blkuc13" "4160,896.67" "1" "1" "180")
(command "_insert" "blkuc13" "4160,897.41" "1" "1" "0")
(command "_insert" "blkuc13" "4160,897.04" "1" "1" "180")
(command "_insert" "blkuc13" "4160,897.78" "1" "1" "0")
(command "_insert" "blkuc13" "4160,897.41" "1" "1" "180")
(command "_insert" "blkuc13" "4160,898.15" "1" "1" "0")
(command "_insert" "blkuc13" "4160,897.78" "1" "1" "180")
(command "_insert" "blkuc13" "4160,898.52" "1" "1" "0")
(command "_insert" "blkuc13" "4160,898.15" "1" "1" "180")
(command "_insert" "blkuc13" "4160,898.89" "1" "1" "0")
(command "_insert" "blkuc13" "4160,898.52" "1" "1" "180")
(command "_insert" "blkuc13" "4160,899.26" "1" "1" "0")
(command "_insert" "blkuc13" "4160,898.89" "1" "1" "180")
(command "_insert" "blkuc13" "4160,899.63" "1" "1" "0")
(command "_insert" "blkuc13" "4160,899.26" "1" "1" "180")
(command "_insert" "blkuc13" "4160,900" "1" "1" "0")
(command "_insert" "blkuc13" "4160,899.63" "1" "1" "180")
(command "_insert" "blkuc13" "4160,900.37" "1" "1" "0")
(command "_insert" "blkuc13" "4160,900" "1" "1" "180")
(command "_insert" "blkuc13" "4160,900.74" "1" "1" "0")
(command "_insert" "blkuc13" "4160,900.37" "1" "1" "180")
(command "_insert" "blkuc13" "4160,901.11" "1" "1" "0")
(command "_insert" "blkuc13" "4160,900.74" "1" "1" "180")
(command "_insert" "blkuc13" "4160,901.48" "1" "1" "0")
(command "_insert" "blkuc13" "4160,901.11" "1" "1" "180")
(command "_insert" "blkuc13" "4160,901.85" "1" "1" "0")
(command "_insert" "blkuc13" "4160,901.48" "1" "1" "180")
(command "_insert" "blkuc13" "4160,902.22" "1" "1" "0")
(command "_insert" "blkuc13" "4160,901.85" "1" "1" "180")
(command "_insert" "blkuc13" "4160,902.59" "1" "1" "0")
(command "_insert" "blkuc13" "4160,902.22" "1" "1" "180")
(command "_insert" "blkuc13" "4160,902.96" "1" "1" "0")
(command "_insert" "blkuc13" "4160,902.59" "1" "1" "180")
(command "_insert" "blkuc13" "4160,903.33" "1" "1" "0")
(command "_insert" "blkuc13" "4160,902.96" "1" "1" "180")
(command "_insert" "blkuc13" "4160,903.7" "1" "1" "0")
(command "_insert" "blkuc13" "4160,903.33" "1" "1" "180")
(command "_insert" "blkuc13" "4160,904.07" "1" "1" "0")
(command "_insert" "blkuc13" "4160,903.7" "1" "1" "180")
(command "_insert" "blkuc13" "4160,904.44" "1" "1" "0")
(command "_insert" "blkuc13" "4160,904.07" "1" "1" "180")
(command "_insert" "blkuc13" "4160,904.81" "1" "1" "0")
(command "_insert" "blkuc13" "4160,904.44" "1" "1" "180")
(command "_insert" "blkuc13" "4160,905.18" "1" "1" "0")
(command "_insert" "blkuc13" "4160,904.81" "1" "1" "180")
(command "_insert" "blkuc13" "4160,905.55" "1" "1" "0")
(command "_insert" "blkuc13" "4160,905.18" "1" "1" "180")
(command "_insert" "blkuc13" "4160,905.92" "1" "1" "0")
(command "_insert" "blkuc13" "4160,905.55" "1" "1" "180")
(command "_insert" "blkuc13" "4160,906.29" "1" "1" "0")
(command "_insert" "blkuc13" "4160,905.92" "1" "1" "180")
(command "_insert" "blkuc13" "4160,906.66" "1" "1" "0")
(command "_insert" "blkuc13" "4160,906.29" "1" "1" "180")
(command "_insert" "blkuc13" "4160,907.03" "1" "1" "0")
(command "_insert" "blkuc13" "4160,906.66" "1" "1" "180")
(command "_insert" "blkuc13" "4160,907.4" "1" "1" "0")
(command "_insert" "blkuc13" "4160,907.03" "1" "1" "180")
(command "_insert" "blkuc13" "4160,907.77" "1" "1" "0")
(command "_insert" "blkuc13" "4160,907.4" "1" "1" "180")
(command "_insert" "blkuc13" "4160,908.14" "1" "1" "0")
(command "_insert" "blkuc13" "4160,907.77" "1" "1" "180")
(command "_insert" "blkuc13" "4160,908.51" "1" "1" "0")
(command "_insert" "blkuc13" "4160,908.14" "1" "1" "180")
(command "_insert" "blkuc13" "4160,908.88" "1" "1" "0")
(command "_insert" "blkuc13" "4160,908.51" "1" "1" "180")
(command "_insert" "blkuc13" "4160,909.25" "1" "1" "0")
(command "_insert" "blkuc13" "4160,908.88" "1" "1" "180")
(command "_insert" "blkuc13" "4160,909.62" "1" "1" "0")
(command "_insert" "blkuc13" "4160,909.25" "1" "1" "180")
(command "_insert" "blkuc13" "4160,909.99" "1" "1" "0")
(command "_insert" "blkuc13" "4160,909.62" "1" "1" "180")
(command "_insert" "blkuc13" "4160,910.36" "1" "1" "0")
(command "_insert" "blkuc13" "4160,909.99" "1" "1" "180")
(command "_insert" "blkuc13" "4160,910.73" "1" "1" "0")
(command "_insert" "blkuc13" "4160,910.36" "1" "1" "180")
(command "_insert" "blkuc13" "4160,911.1" "1" "1" "0")
(command "_insert" "blkuc13" "4160,910.73" "1" "1" "180")
(command "_insert" "blkuc13" "4160,911.47" "1" "1" "0")
(command "_insert" "blkuc13" "4160,911.1" "1" "1" "180")
(command "_insert" "blkuc13" "4160,911.84" "1" "1" "0")
(command "_insert" "blkuc13" "4160,911.47" "1" "1" "180")
(command "_insert" "blkuc13" "4160,912.21" "1" "1" "0")
(command "_insert" "blkuc13" "4160,911.84" "1" "1" "180")
(command "_insert" "blkuc13" "4160,912.58" "1" "1" "0")
(command "_insert" "blkuc13" "4160,912.21" "1" "1" "180")
(command "_insert" "blkuc13" "4160,912.95" "1" "1" "0")
(command "_insert" "blkuc13" "4160,912.58" "1" "1" "180")
(command "_insert" "blkuc13" "4160,913.32" "1" "1" "0")
(command "_insert" "blkuc13" "4160,912.95" "1" "1" "180")
(command "_insert" "blkuc13" "4160,913.69" "1" "1" "0")
(command "_insert" "blkuc13" "4160,913.32" "1" "1" "180")
(command "_insert" "blkuc13" "4160,914.06" "1" "1" "0")
(command "_insert" "blkuc13" "4160,913.69" "1" "1" "180")
(command "_insert" "blkuc13" "4160,914.43" "1" "1" "0")
(command "_insert" "blkuc13" "4160,914.06" "1" "1" "180")
(command "_insert" "blkuc13" "4160,914.8" "1" "1" "0")
(command "_insert" "blkuc13" "4160,914.43" "1" "1" "180")
(command "_insert" "blkuc13" "4160,915.17" "1" "1" "0")
(command "_insert" "blkuc13" "4160,914.8" "1" "1" "180")
(command "_insert" "blkuc13" "4160,915.54" "1" "1" "0")
(command "_insert" "blkuc13" "4160,915.17" "1" "1" "180")
(command "_insert" "blkuc13" "4160,915.91" "1" "1" "0")
(command "_insert" "blkuc13" "4160,915.54" "1" "1" "180")
(command "_insert" "blkuc13" "4160,916.28" "1" "1" "0")
(command "_insert" "blkuc13" "4160,915.91" "1" "1" "180")
(command "_insert" "blkuc13" "4160,916.65" "1" "1" "0")
(command "_insert" "blkuc13" "4160,916.28" "1" "1" "180")
(command "_insert" "blkuc13" "4160,917.02" "1" "1" "0")
(command "_insert" "blkuc13" "4160,916.65" "1" "1" "180")
(command "_insert" "blkuc13" "4160,917.39" "1" "1" "0")
(command "_insert" "blkuc13" "4160,917.02" "1" "1" "180")
(command "_insert" "blkuc13" "4160,917.76" "1" "1" "0")
(command "_insert" "blkuc13" "4160,917.39" "1" "1" "180")
(command "_insert" "blkuc13" "4160,918.13" "1" "1" "0")
(command "_insert" "blkuc13" "4160,917.76" "1" "1" "180")
(command "_insert" "blkuc13" "4160,918.5" "1" "1" "0")
(command "_insert" "blkuc13" "4160,918.13" "1" "1" "180")
(command "_insert" "blkuc13" "4160,918.87" "1" "1" "0")
(command "_insert" "blkuc13" "4160,918.5" "1" "1" "180")
(command "_insert" "blkuc13" "4160,919.24" "1" "1" "0")
(command "_insert" "blkuc13" "4160,918.87" "1" "1" "180")
(command "_insert" "blkuc13" "4160,919.61" "1" "1" "0")
(command "_insert" "blkuc13" "4160,919.24" "1" "1" "180")
(command "_insert" "blkuc13" "4160,919.98" "1" "1" "0")
(command "_insert" "blkuc13" "4160,919.61" "1" "1" "180")
(command "_insert" "blkuc13" "4160,920.35" "1" "1" "0")
(command "_insert" "blkuc13" "4160,919.98" "1" "1" "180")
(command "_insert" "blkuc13" "4160,920.72" "1" "1" "0")
(command "_insert" "blkuc13" "4160,920.35" "1" "1" "180")
(command "_insert" "blkuc13" "4160,921.09" "1" "1" "0")
(command "_insert" "blkuc13" "4160,920.72" "1" "1" "180")
(command "_insert" "blkuc13" "4160,921.46" "1" "1" "0")
(command "_insert" "blkuc13" "4160,921.09" "1" "1" "180")
(command "_insert" "blkuc13" "4160,921.83" "1" "1" "0")
(command "_insert" "blkuc13" "4160,921.46" "1" "1" "180")
(command "_insert" "blkuc13" "4160,922.2" "1" "1" "0")
(command "_insert" "blkuc13" "4160,921.83" "1" "1" "180")
(command "_insert" "blkuc13" "4160,922.57" "1" "1" "0")
(command "_insert" "blkuc13" "4160,922.2" "1" "1" "180")
(command "_insert" "blkuc13" "4160,922.94" "1" "1" "0")
(command "_insert" "blkuc13" "4160,922.57" "1" "1" "180")
(command "_insert" "blkuc13" "4160,923.31" "1" "1" "0")
(command "_insert" "blkuc13" "4160,922.94" "1" "1" "180")
(command "_insert" "blkuc13" "4160,923.68" "1" "1" "0")
(command "_insert" "blkuc13" "4160,923.31" "1" "1" "180")
(command "_insert" "blkuc13" "4160,924.05" "1" "1" "0")
(command "_insert" "blkuc13" "4160,923.68" "1" "1" "180")
(command "_insert" "blkuc13" "4160,924.42" "1" "1" "0")
(command "_insert" "blkuc13" "4160,924.05" "1" "1" "180")
(command "_insert" "blkuc13" "4160,924.79" "1" "1" "0")
(command "_insert" "blkuc13" "4160,924.42" "1" "1" "180")
(command "_insert" "blkuc13" "4160,925.16" "1" "1" "0")
(command "_insert" "blkuc13" "4160,924.79" "1" "1" "180")
(command "_insert" "blkuc13" "4160,925.53" "1" "1" "0")
(command "_insert" "blkuc13" "4160,925.16" "1" "1" "180")
(command "_insert" "blkuc13" "4160,925.9" "1" "1" "0")
(command "_insert" "blkuc13" "4160,925.53" "1" "1" "180")
(command "_insert" "blkuc13" "4160,926.27" "1" "1" "0")
(command "_insert" "blkuc13" "4160,925.9" "1" "1" "180")
(command "_insert" "blkuc13" "4160,926.64" "1" "1" "0")
(command "_insert" "blkuc13" "4160,926.27" "1" "1" "180")
(command "_insert" "blkuc13" "4160,927.01" "1" "1" "0")
(command "_insert" "blkuc13" "4160,926.64" "1" "1" "180")
(command "_insert" "blkuc13" "4160,927.38" "1" "1" "0")
(command "_insert" "blkuc13" "4160,927.01" "1" "1" "180")
(command "_insert" "blkuc13" "4160,927.75" "1" "1" "0")
(command "_insert" "blkuc13" "4160,927.38" "1" "1" "180")
(command "_layer" "set" "phccover" "")
(command "_rectangle" "4158.904,933.3" "4161.096,866.7")
(command "_layer" "set" "nitride" "")
(setq phc13 currobj)
(command "_layer" "set" "cover" "")
(command "_rectangle" "4158.904,836.7" "4161.096,963.3")
(command "_layer" "set" "nitride" "")
(command "_layer" "set" "text" "")
(command "_circle" "4157.954,846.7" "0.075")
(command "_circle" "4157.579,846.7" "0.15")
(command "_circle" "4157.204,846.7" "0.075")
(command "_circle" "4156.829,846.7" "0.15")
(command "_circle" "4157.954,848.7" "0.075")
(command "_circle" "4157.579,848.7" "0.075")
(command "_circle" "4157.204,848.7" "0.15")
(command "_circle" "4156.829,848.7" "0.15")
(command "_circle" "4157.954,850.7" "0.075")
(command "_circle" "4157.579,850.7" "0.15")
(command "_circle" "4157.204,850.7" "0.15")
(command "_circle" "4156.829,850.7" "0.15")
(command "_circle" "4157.954,852.7" "0.075")
(command "_circle" "4157.579,852.7" "0.075")
(command "_circle" "4157.204,852.7" "0.075")
(command "_circle" "4156.829,852.7" "0.075")
(command "_circle" "4156.454,852.7" "0.15")
(command "_circle" "4157.954,854.7" "0.075")
(command "_circle" "4157.579,854.7" "0.15")
(command "_circle" "4157.204,854.7" "0.075")
(command "_circle" "4156.829,854.7" "0.075")
(command "_circle" "4156.454,854.7" "0.15")
(command "_circle" "4157.954,856.7" "0.075")
(command "_circle" "4157.579,856.7" "0.075")
(command "_circle" "4157.204,856.7" "0.15")
(command "_circle" "4156.829,856.7" "0.075")
(command "_circle" "4156.454,856.7" "0.15")
(command "_circle" "4157.954,858.7" "0.075")
(command "_circle" "4157.579,858.7" "0.15")
(command "_circle" "4157.204,858.7" "0.15")
(command "_circle" "4156.829,858.7" "0.075")
(command "_circle" "4156.454,858.7" "0.15")
(command "_circle" "4157.954,860.7" "0.075")
(command "_circle" "4157.579,860.7" "0.075")
(command "_circle" "4157.204,860.7" "0.075")
(command "_circle" "4156.829,860.7" "0.15")
(command "_circle" "4156.454,860.7" "0.15")
(command "_circle" "4157.954,862.7" "0.075")
(command "_circle" "4157.579,862.7" "0.15")
(command "_circle" "4157.204,862.7" "0.075")
(command "_circle" "4156.829,862.7" "0.15")
(command "_circle" "4156.454,862.7" "0.15")
(command "_circle" "4157.954,864.7" "0.075")
(command "_circle" "4157.579,864.7" "0.075")
(command "_circle" "4157.204,864.7" "0.15")
(command "_circle" "4156.829,864.7" "0.15")
(command "_circle" "4156.454,864.7" "0.15")
(command "_circle" "4157.954,866.7" "0.075")
(command "_circle" "4157.579,866.7" "0.15")
(command "_circle" "4157.204,866.7" "0.15")
(command "_circle" "4156.829,866.7" "0.15")
(command "_circle" "4156.454,866.7" "0.15")
(command "_circle" "4157.954,868.7" "0.075")
(command "_circle" "4157.579,868.7" "0.075")
(command "_circle" "4157.204,868.7" "0.075")
(command "_circle" "4156.829,868.7" "0.075")
(command "_circle" "4156.454,868.7" "0.075")
(command "_circle" "4156.079,868.7" "0.15")
(command "_circle" "4157.954,870.7" "0.075")
(command "_circle" "4157.579,870.7" "0.15")
(command "_circle" "4157.204,870.7" "0.075")
(command "_circle" "4156.829,870.7" "0.075")
(command "_circle" "4156.454,870.7" "0.075")
(command "_circle" "4156.079,870.7" "0.15")
(command "_circle" "4157.954,872.7" "0.075")
(command "_circle" "4157.579,872.7" "0.075")
(command "_circle" "4157.204,872.7" "0.15")
(command "_circle" "4156.829,872.7" "0.075")
(command "_circle" "4156.454,872.7" "0.075")
(command "_circle" "4156.079,872.7" "0.15")
(command "_circle" "4157.954,874.7" "0.075")
(command "_circle" "4157.579,874.7" "0.15")
(command "_circle" "4157.204,874.7" "0.15")
(command "_circle" "4156.829,874.7" "0.075")
(command "_circle" "4156.454,874.7" "0.075")
(command "_circle" "4156.079,874.7" "0.15")
(command "_circle" "4157.954,876.7" "0.075")
(command "_circle" "4157.579,876.7" "0.075")
(command "_circle" "4157.204,876.7" "0.075")
(command "_circle" "4156.829,876.7" "0.15")
(command "_circle" "4156.454,876.7" "0.075")
(command "_circle" "4156.079,876.7" "0.15")
(command "_circle" "4157.954,878.7" "0.075")
(command "_circle" "4157.579,878.7" "0.15")
(command "_circle" "4157.204,878.7" "0.075")
(command "_circle" "4156.829,878.7" "0.15")
(command "_circle" "4156.454,878.7" "0.075")
(command "_circle" "4156.079,878.7" "0.15")
(command "_circle" "4157.954,880.7" "0.075")
(command "_circle" "4157.579,880.7" "0.075")
(command "_circle" "4157.204,880.7" "0.15")
(command "_circle" "4156.829,880.7" "0.15")
(command "_circle" "4156.454,880.7" "0.075")
(command "_circle" "4156.079,880.7" "0.15")
(command "_circle" "4157.954,882.7" "0.075")
(command "_circle" "4157.579,882.7" "0.15")
(command "_circle" "4157.204,882.7" "0.15")
(command "_circle" "4156.829,882.7" "0.15")
(command "_circle" "4156.454,882.7" "0.075")
(command "_circle" "4156.079,882.7" "0.15")
(command "_circle" "4157.954,884.7" "0.075")
(command "_circle" "4157.579,884.7" "0.075")
(command "_circle" "4157.204,884.7" "0.075")
(command "_circle" "4156.829,884.7" "0.075")
(command "_circle" "4156.454,884.7" "0.15")
(command "_circle" "4156.079,884.7" "0.15")
(command "_circle" "4157.954,886.7" "0.075")
(command "_circle" "4157.579,886.7" "0.15")
(command "_circle" "4157.204,886.7" "0.075")
(command "_circle" "4156.829,886.7" "0.075")
(command "_circle" "4156.454,886.7" "0.15")
(command "_circle" "4156.079,886.7" "0.15")
(command "_circle" "4157.954,888.7" "0.075")
(command "_circle" "4157.579,888.7" "0.075")
(command "_circle" "4157.204,888.7" "0.15")
(command "_circle" "4156.829,888.7" "0.075")
(command "_circle" "4156.454,888.7" "0.15")
(command "_circle" "4156.079,888.7" "0.15")
(command "_circle" "4157.954,890.7" "0.075")
(command "_circle" "4157.579,890.7" "0.15")
(command "_circle" "4157.204,890.7" "0.15")
(command "_circle" "4156.829,890.7" "0.075")
(command "_circle" "4156.454,890.7" "0.15")
(command "_circle" "4156.079,890.7" "0.15")
(command "_circle" "4157.954,892.7" "0.075")
(command "_circle" "4157.579,892.7" "0.075")
(command "_circle" "4157.204,892.7" "0.075")
(command "_circle" "4156.829,892.7" "0.15")
(command "_circle" "4156.454,892.7" "0.15")
(command "_circle" "4156.079,892.7" "0.15")
(command "_circle" "4157.954,894.7" "0.075")
(command "_circle" "4157.579,894.7" "0.15")
(command "_circle" "4157.204,894.7" "0.075")
(command "_circle" "4156.829,894.7" "0.15")
(command "_circle" "4156.454,894.7" "0.15")
(command "_circle" "4156.079,894.7" "0.15")
(command "_circle" "4157.954,896.7" "0.075")
(command "_circle" "4157.579,896.7" "0.075")
(command "_circle" "4157.204,896.7" "0.15")
(command "_circle" "4156.829,896.7" "0.15")
(command "_circle" "4156.454,896.7" "0.15")
(command "_circle" "4156.079,896.7" "0.15")
(command "_circle" "4157.954,898.7" "0.075")
(command "_circle" "4157.579,898.7" "0.15")
(command "_circle" "4157.204,898.7" "0.15")
(command "_circle" "4156.829,898.7" "0.15")
(command "_circle" "4156.454,898.7" "0.15")
(command "_circle" "4156.079,898.7" "0.15")
(command "_circle" "4157.954,900.7" "0.075")
(command "_circle" "4157.579,900.7" "0.075")
(command "_circle" "4157.204,900.7" "0.075")
(command "_circle" "4156.829,900.7" "0.075")
(command "_circle" "4156.454,900.7" "0.075")
(command "_circle" "4156.079,900.7" "0.075")
(command "_circle" "4155.704,900.7" "0.15")
(command "_circle" "4157.954,902.7" "0.075")
(command "_circle" "4157.579,902.7" "0.15")
(command "_circle" "4157.204,902.7" "0.075")
(command "_circle" "4156.829,902.7" "0.075")
(command "_circle" "4156.454,902.7" "0.075")
(command "_circle" "4156.079,902.7" "0.075")
(command "_circle" "4155.704,902.7" "0.15")
(command "_circle" "4157.954,904.7" "0.075")
(command "_circle" "4157.579,904.7" "0.075")
(command "_circle" "4157.204,904.7" "0.15")
(command "_circle" "4156.829,904.7" "0.075")
(command "_circle" "4156.454,904.7" "0.075")
(command "_circle" "4156.079,904.7" "0.075")
(command "_circle" "4155.704,904.7" "0.15")
(command "_circle" "4157.954,906.7" "0.075")
(command "_circle" "4157.579,906.7" "0.15")
(command "_circle" "4157.204,906.7" "0.15")
(command "_circle" "4156.829,906.7" "0.075")
(command "_circle" "4156.454,906.7" "0.075")
(command "_circle" "4156.079,906.7" "0.075")
(command "_circle" "4155.704,906.7" "0.15")
(command "_circle" "4157.954,908.7" "0.075")
(command "_circle" "4157.579,908.7" "0.075")
(command "_circle" "4157.204,908.7" "0.075")
(command "_circle" "4156.829,908.7" "0.15")
(command "_circle" "4156.454,908.7" "0.075")
(command "_circle" "4156.079,908.7" "0.075")
(command "_circle" "4155.704,908.7" "0.15")
(command "_circle" "4157.954,910.7" "0.075")
(command "_circle" "4157.579,910.7" "0.15")
(command "_circle" "4157.204,910.7" "0.075")
(command "_circle" "4156.829,910.7" "0.15")
(command "_circle" "4156.454,910.7" "0.075")
(command "_circle" "4156.079,910.7" "0.075")
(command "_circle" "4155.704,910.7" "0.15")
(command "_circle" "4157.954,912.7" "0.075")
(command "_circle" "4157.579,912.7" "0.075")
(command "_circle" "4157.204,912.7" "0.15")
(command "_circle" "4156.829,912.7" "0.15")
(command "_circle" "4156.454,912.7" "0.075")
(command "_circle" "4156.079,912.7" "0.075")
(command "_circle" "4155.704,912.7" "0.15")
(command "_circle" "4157.954,914.7" "0.075")
(command "_circle" "4157.579,914.7" "0.15")
(command "_circle" "4157.204,914.7" "0.15")
(command "_circle" "4156.829,914.7" "0.15")
(command "_circle" "4156.454,914.7" "0.075")
(command "_circle" "4156.079,914.7" "0.075")
(command "_circle" "4155.704,914.7" "0.15")
(command "_circle" "4157.954,916.7" "0.075")
(command "_circle" "4157.579,916.7" "0.075")
(command "_circle" "4157.204,916.7" "0.075")
(command "_circle" "4156.829,916.7" "0.075")
(command "_circle" "4156.454,916.7" "0.15")
(command "_circle" "4156.079,916.7" "0.075")
(command "_circle" "4155.704,916.7" "0.15")
(command "_circle" "4157.954,918.7" "0.075")
(command "_circle" "4157.579,918.7" "0.15")
(command "_circle" "4157.204,918.7" "0.075")
(command "_circle" "4156.829,918.7" "0.075")
(command "_circle" "4156.454,918.7" "0.15")
(command "_circle" "4156.079,918.7" "0.075")
(command "_circle" "4155.704,918.7" "0.15")
(command "_circle" "4157.954,920.7" "0.075")
(command "_circle" "4157.579,920.7" "0.075")
(command "_circle" "4157.204,920.7" "0.15")
(command "_circle" "4156.829,920.7" "0.075")
(command "_circle" "4156.454,920.7" "0.15")
(command "_circle" "4156.079,920.7" "0.075")
(command "_circle" "4155.704,920.7" "0.15")
(command "_circle" "4157.954,922.7" "0.075")
(command "_circle" "4157.579,922.7" "0.15")
(command "_circle" "4157.204,922.7" "0.15")
(command "_circle" "4156.829,922.7" "0.075")
(command "_circle" "4156.454,922.7" "0.15")
(command "_circle" "4156.079,922.7" "0.075")
(command "_circle" "4155.704,922.7" "0.15")
(command "_circle" "4157.954,924.7" "0.075")
(command "_circle" "4157.579,924.7" "0.075")
(command "_circle" "4157.204,924.7" "0.075")
(command "_circle" "4156.829,924.7" "0.15")
(command "_circle" "4156.454,924.7" "0.15")
(command "_circle" "4156.079,924.7" "0.075")
(command "_circle" "4155.704,924.7" "0.15")
(command "_circle" "4157.954,926.7" "0.075")
(command "_circle" "4157.579,926.7" "0.15")
(command "_circle" "4157.204,926.7" "0.075")
(command "_circle" "4156.829,926.7" "0.15")
(command "_circle" "4156.454,926.7" "0.15")
(command "_circle" "4156.079,926.7" "0.075")
(command "_circle" "4155.704,926.7" "0.15")
(command "_circle" "4157.954,928.7" "0.075")
(command "_circle" "4157.579,928.7" "0.075")
(command "_circle" "4157.204,928.7" "0.15")
(command "_circle" "4156.829,928.7" "0.15")
(command "_circle" "4156.454,928.7" "0.15")
(command "_circle" "4156.079,928.7" "0.075")
(command "_circle" "4155.704,928.7" "0.15")
(command "_circle" "4157.954,930.7" "0.075")
(command "_circle" "4157.579,930.7" "0.15")
(command "_circle" "4157.204,930.7" "0.15")
(command "_circle" "4156.829,930.7" "0.15")
(command "_circle" "4156.454,930.7" "0.15")
(command "_circle" "4156.079,930.7" "0.075")
(command "_circle" "4155.704,930.7" "0.15")
(command "_circle" "4157.954,932.7" "0.075")
(command "_circle" "4157.579,932.7" "0.075")
(command "_circle" "4157.204,932.7" "0.075")
(command "_circle" "4156.829,932.7" "0.075")
(command "_circle" "4156.454,932.7" "0.075")
(command "_circle" "4156.079,932.7" "0.15")
(command "_circle" "4155.704,932.7" "0.15")
(command "_circle" "4157.954,934.7" "0.075")
(command "_circle" "4157.579,934.7" "0.15")
(command "_circle" "4157.204,934.7" "0.075")
(command "_circle" "4156.829,934.7" "0.075")
(command "_circle" "4156.454,934.7" "0.075")
(command "_circle" "4156.079,934.7" "0.15")
(command "_circle" "4155.704,934.7" "0.15")
(command "_circle" "4157.954,936.7" "0.075")
(command "_circle" "4157.579,936.7" "0.075")
(command "_circle" "4157.204,936.7" "0.15")
(command "_circle" "4156.829,936.7" "0.075")
(command "_circle" "4156.454,936.7" "0.075")
(command "_circle" "4156.079,936.7" "0.15")
(command "_circle" "4155.704,936.7" "0.15")
(command "_circle" "4157.954,938.7" "0.075")
(command "_circle" "4157.579,938.7" "0.15")
(command "_circle" "4157.204,938.7" "0.15")
(command "_circle" "4156.829,938.7" "0.075")
(command "_circle" "4156.454,938.7" "0.075")
(command "_circle" "4156.079,938.7" "0.15")
(command "_circle" "4155.704,938.7" "0.15")
(command "_circle" "4157.954,940.7" "0.075")
(command "_circle" "4157.579,940.7" "0.075")
(command "_circle" "4157.204,940.7" "0.075")
(command "_circle" "4156.829,940.7" "0.15")
(command "_circle" "4156.454,940.7" "0.075")
(command "_circle" "4156.079,940.7" "0.15")
(command "_circle" "4155.704,940.7" "0.15")
(command "_circle" "4157.954,942.7" "0.075")
(command "_circle" "4157.579,942.7" "0.15")
(command "_circle" "4157.204,942.7" "0.075")
(command "_circle" "4156.829,942.7" "0.15")
(command "_circle" "4156.454,942.7" "0.075")
(command "_circle" "4156.079,942.7" "0.15")
(command "_circle" "4155.704,942.7" "0.15")
(command "_circle" "4157.954,944.7" "0.075")
(command "_circle" "4157.579,944.7" "0.075")
(command "_circle" "4157.204,944.7" "0.15")
(command "_circle" "4156.829,944.7" "0.15")
(command "_circle" "4156.454,944.7" "0.075")
(command "_circle" "4156.079,944.7" "0.15")
(command "_circle" "4155.704,944.7" "0.15")
(command "_circle" "4157.954,946.7" "0.075")
(command "_circle" "4157.579,946.7" "0.15")
(command "_circle" "4157.204,946.7" "0.15")
(command "_circle" "4156.829,946.7" "0.15")
(command "_circle" "4156.454,946.7" "0.075")
(command "_circle" "4156.079,946.7" "0.15")
(command "_circle" "4155.704,946.7" "0.15")
(command "_circle" "4157.954,948.7" "0.075")
(command "_circle" "4157.579,948.7" "0.075")
(command "_circle" "4157.204,948.7" "0.075")
(command "_circle" "4156.829,948.7" "0.075")
(command "_circle" "4156.454,948.7" "0.15")
(command "_circle" "4156.079,948.7" "0.15")
(command "_circle" "4155.704,948.7" "0.15")
(command "_circle" "4157.954,950.7" "0.075")
(command "_circle" "4157.579,950.7" "0.15")
(command "_circle" "4157.204,950.7" "0.075")
(command "_circle" "4156.829,950.7" "0.075")
(command "_circle" "4156.454,950.7" "0.15")
(command "_circle" "4156.079,950.7" "0.15")
(command "_circle" "4155.704,950.7" "0.15")
(command "_circle" "4157.954,952.7" "0.075")
(command "_circle" "4157.579,952.7" "0.075")
(command "_circle" "4157.204,952.7" "0.15")
(command "_circle" "4156.829,952.7" "0.075")
(command "_circle" "4156.454,952.7" "0.15")
(command "_circle" "4156.079,952.7" "0.15")
(command "_circle" "4155.704,952.7" "0.15")
(command "_circle" "4157.954,954.7" "0.075")
(command "_circle" "4157.579,954.7" "0.15")
(command "_circle" "4157.204,954.7" "0.15")
(command "_circle" "4156.829,954.7" "0.075")
(command "_circle" "4156.454,954.7" "0.15")
(command "_circle" "4156.079,954.7" "0.15")
(command "_circle" "4155.704,954.7" "0.15")
(command "_circle" "4157.954,956.7" "0.075")
(command "_circle" "4157.579,956.7" "0.075")
(command "_circle" "4157.204,956.7" "0.075")
(command "_circle" "4156.829,956.7" "0.15")
(command "_circle" "4156.454,956.7" "0.15")
(command "_circle" "4156.079,956.7" "0.15")
(command "_circle" "4155.704,956.7" "0.15")
(command "_circle" "4157.954,958.7" "0.075")
(command "_circle" "4157.579,958.7" "0.15")
(command "_circle" "4157.204,958.7" "0.075")
(command "_circle" "4156.829,958.7" "0.15")
(command "_circle" "4156.454,958.7" "0.15")
(command "_circle" "4156.079,958.7" "0.15")
(command "_circle" "4155.704,958.7" "0.15")
(command "_circle" "4157.954,960.7" "0.075")
(command "_circle" "4157.579,960.7" "0.075")
(command "_circle" "4157.204,960.7" "0.15")
(command "_circle" "4156.829,960.7" "0.15")
(command "_circle" "4156.454,960.7" "0.15")
(command "_circle" "4156.079,960.7" "0.15")
(command "_circle" "4155.704,960.7" "0.15")
(command "_circle" "4157.954,962.7" "0.075")
(command "_circle" "4157.579,962.7" "0.15")
(command "_circle" "4157.204,962.7" "0.15")
(command "_circle" "4156.829,962.7" "0.15")
(command "_circle" "4156.454,962.7" "0.15")
(command "_circle" "4156.079,962.7" "0.15")
(command "_circle" "4155.704,962.7" "0.15")
(command "_layer" "set" "nitride" "")
(command "_layer" "set" "text" "")
(command-s "_text" "4146.904,963.3" "2" "-90" "a = 370 nm" )
(sssetfirst nil (ssget "_L"))
(if (not (numberp (vl-string-search "Mac" (getvar "platform")))) (c:txtexp))
(command "_layer" "set" "nitride" "")
(command "_layer" "set" "text" "")
(command-s "_text" "4143.904,963.3" "2" "-90" "gap = 270 nm" )
(sssetfirst nil (ssget "_L"))
(if (not (numberp (vl-string-search "Mac" (getvar "platform")))) (c:txtexp))
(command "_layer" "set" "nitride" "")
(command "_layer" "set" "text" "")
(command-s "_text" "4140.904,963.3" "2" "-90" "amplitude = 122 nm" )
(sssetfirst nil (ssget "_L"))
(if (not (numberp (vl-string-search "Mac" (getvar "platform")))) (c:txtexp))
(command "_layer" "set" "nitride" "")
(command "_layer" "set" "text" "")
(command-s "_text" "4137.904,963.3" "2" "-90" "start width = 280 nm" )
(sssetfirst nil (ssget "_L"))
(if (not (numberp (vl-string-search "Mac" (getvar "platform")))) (c:txtexp))
(command "_layer" "set" "nitride" "")
(command "_layer" "set" "text" "")
(command-s "_text" "4134.904,963.3" "2" "-90" "width = 291 nm" )
(sssetfirst nil (ssget "_L"))
(if (not (numberp (vl-string-search "Mac" (getvar "platform")))) (c:txtexp))
(command "_layer" "set" "nitride" "")
(command "_layer" "set" "text" "")
(command-s "_text" "4131.904,963.3" "2" "-90" "taper: 15" )
(sssetfirst nil (ssget "_L"))
(if (not (numberp (vl-string-search "Mac" (getvar "platform")))) (c:txtexp))
(command "_layer" "set" "nitride" "")
(command "_layer" "set" "text" "")
(command-s "_text" "4128.904,963.3" "2" "-90" "nominal: 150" )
(sssetfirst nil (ssget "_L"))
(if (not (numberp (vl-string-search "Mac" (getvar "platform")))) (c:txtexp))
(command "_layer" "set" "nitride" "")
(command "_layer" "set" "indicators" "")
(setq coords (list 
(list 4080.415 940) 
(list 4080.415 920) 
(list 4060.415 900) 
(list 4080.415 880) 
(list 4080.415 860) 
(list 4080.415 900) 
(list 4080.415 887.0711) 
(list 4067.4861 900) 
(list 4080.415 912.9289) 
(list 4080.415 900)))
(apply 'command (append '("pline") coords '("c")))
(command "._fillet" "radius" "1" "._fillet" "P" (entlast))
(setq coords (list 
(list 4239.585 940) 
(list 4239.585 920) 
(list 4259.585 900) 
(list 4239.585 880) 
(list 4239.585 860) 
(list 4239.585 900) 
(list 4239.585 887.0711) 
(list 4252.5139 900) 
(list 4239.585 912.9289) 
(list 4239.585 900)))
(apply 'command (append '("pline") coords '("c")))
(command "._fillet" "radius" "1" "._fillet" "P" (entlast))
(command "_layer" "set" "holes" "")
(command "_circle" "4078.0629,914.1124" "0.5")
(command "_circle" "4075.7109,911.7603" "0.5")
(command "_circle" "4073.3588,909.4083" "0.5")
(command "_circle" "4071.0067,907.0562" "0.5")
(command "_circle" "4068.6547,904.7041" "0.5")
(command "_circle" "4066.3026,902.3521" "0.5")
(command "_circle" "4063.9505,900" "0.5")
(command "_circle" "4066.3026,897.6479" "0.5")
(command "_circle" "4068.6547,895.2959" "0.5")
(command "_circle" "4071.0067,892.9438" "0.5")
(command "_circle" "4073.3588,890.5917" "0.5")
(command "_circle" "4075.7109,888.2397" "0.5")
(command "_circle" "4078.0629,885.8876" "0.5")
(command "_circle" "4241.9371,914.1124" "0.5")
(command "_circle" "4244.2891,911.7603" "0.5")
(command "_circle" "4246.6412,909.4083" "0.5")
(command "_circle" "4248.9933,907.0562" "0.5")
(command "_circle" "4251.3453,904.7041" "0.5")
(command "_circle" "4253.6974,902.3521" "0.5")
(command "_circle" "4256.0495,900" "0.5")
(command "_circle" "4253.6974,897.6479" "0.5")
(command "_circle" "4251.3453,895.2959" "0.5")
(command "_circle" "4248.9933,892.9438" "0.5")
(command "_circle" "4246.6412,890.5917" "0.5")
(command "_circle" "4244.2891,888.2397" "0.5")
(command "_circle" "4241.9371,885.8876" "0.5")
(command "_layer" "set" "nitride" "")
(command "_block" "blkcoupler13" "4160,900" coupler13 "")
(command "_insert" "blkcoupler13" "4160,900" "1" "1" "0")
(command "_insert" "blkcoupler13" "4160,900" "1" "1" "180")
(command "_block" "blksinglenanobeam13" "4160,900" singlenanobeam13 "")
(command "_insert" "blksinglenanobeam13" "4160,900" "1" "1" "0")
(command "_insert" "blksinglenanobeam13" "4160,900" "1" "1" "180")
(command "_block" "blkanglednodearray13" "4160,900" anglednodearray13 "")
(command "_insert" "blkanglednodearray13" "4160,900" "1" "1" "0")
(command "_insert" "blkanglednodearray13" "4160,900" "1" "1" "180")
(command "_block" "blkcooledsinglenanobeam13" "4160,900" cooledsinglenanobeam13 "")
(command "_insert" "blkcooledsinglenanobeam13" "4160,900" "1" "1" "0")
(command "_insert" "blkcooledsinglenanobeam13" "4160,900" "1" "1" "180")
(command "_block" "blkyjunction13" "4160,900" yjunction13 "")
(command "_insert" "blkyjunction13" "4160,900" "1" "1" "0")
(command "_insert" "blkyjunction13" "4160,900" "1" "1" "180")
; DRAWING BULGING VEE GROOVE
(command "_layer" "set" "vgroove" "")
(setq coords (list 
(list 4085.415 -605) 
(list 4085.415 0) 
(list 4085.415 0) 
(list 4085.415 1800) 
(list 4085.415 1800) 
(list 4085.415 2405) 
(list 4234.585 2405) 
(list 4234.585 1800) 
(list 4234.585 1800) 
(list 4234.585 0) 
(list 4234.585 0) 
(list 4234.585 -605)))
(apply 'command (append '("pline") coords '("c")))
(command "._fillet" "radius" "0" "._fillet" "P" (entlast))
(command "_layer" "set" "window" "")
(command "_rectangle" "4085.415,-1935" "4234.585,-600")
(command "_rectangle" "4085.415,2400" "4234.585,5300")
(command "_layer" "set" "grid" "")
(command "_rectangle" "4086.415,-1934" "4109.9433,-1909.2133")
(command "_array" "last" "" "R" "75" "3" "25.7867" "24.5283")
(command "_rectangle" "4161,-1934" "4184.5283,-1909.2133")
(command "_array" "last" "" "R" "75" "3" "25.7867" "24.5283")
(command "_rectangle" "4086.415,1" "4109.9433,25.7")
(command "_array" "last" "" "R" "70" "3" "25.7" "24.5283")
(command "_rectangle" "4161,1" "4184.5283,25.7")
(command "_array" "last" "" "R" "70" "3" "25.7" "24.5283")
(command "_rectangle" "4086.415,1801" "4109.9433,1825.9185")
(command "_array" "last" "" "R" "135" "3" "25.9185" "24.5283")
(command "_rectangle" "4161,1801" "4184.5283,1825.9185")
(command "_array" "last" "" "R" "135" "3" "25.9185" "24.5283")
(command "_layer" "set" "vgrooveFDA" "")
(command "_rectangle" "4234.585,-2233" "4085.415,-1933")
(command "_layer" "set" "nitride" "")
(command "_layer" "set" "holes" "")
(command "_circle" "4237.085,331.5" "0.5")
(command "_array" "last" "" "R" "379" "1" "3" "2.5")
(command "_circle" "4082.915,331.5" "0.5")
(command "_array" "last" "" "R" "379" "1" "3" "-2.5")
(command "_layer" "set" "nitride" "")
(command "_layer" "set" "window" "")
(command "_layer" "set" "window" "")
(command "_rectangle" "4239.585,0" "4400.415,1800")
(command "._fillet" "radius" "20" "._fillet" "P" (entlast))
(command "_layer" "set" "grid" "")
(command "_rectangle" "4240.585,1" "4262.4179,25.7")
(command "_array" "last" "" "R" "70" "7" "25.7" "22.8329")
(command "_layer" "set" "nitride" "")
; DRAWING REGION LAYER
(command "_layer" "set" "regionLayer13" "")
(command "_rectangle" "4080,-460" "4240,2260")
(command "_layer" "set" "nitride" "")
(setq coupler13 nil)
(setq singlenanobeam13 nil)
(setq anglednodearray13 nil)
(setq cooledsinglenanobeam13 nil)
(setq yjunction13 nil)
; DEVICE #14
(command "_layer" "set" "window" "")
(command "_circle" "4392.915,-415" "5")
(command "_circle" "4392.915,-402.5" "5")
(command "_circle" "4392.915,-390" "5")
(command "_circle" "4392.915,-377.5" "5")
(command "_circle" "4380.415,-415" "5")
(command "_circle" "4380.415,-402.5" "5")
(command "_circle" "4380.415,-390" "5")
(command "_circle" "4380.415,-377.5" "5")
(command "_circle" "4367.915,-415" "5")
(command "_circle" "4367.915,-402.5" "5")
(command "_circle" "4367.915,-390" "5")
(command "_circle" "4367.915,-377.5" "5")
(command "_circle" "4355.415,-415" "5")
(command "_circle" "4355.415,-402.5" "5")
(command "_layer" "set" "nitride" "")
(setq currobj nil)
(setq currobj (ssadd))
; DRAWING COUPLER
(setq coords (list 
(list 4480.0675 -415) 
(list 4480.0675 -413) 
(list 4553.585 -413) 
(list 4553.585 -413) 
(list 4553.9677 -413.0761) 
(list 4554.2921 -413.2929) 
(list 4554.5089 -413.6173) 
(list 4554.585 -414) 
(list 4554.585 -411.8) 
(list 4554.585 -411.8) 
(list 4554.5089 -412.1827) 
(list 4554.2921 -412.5071) 
(list 4553.9677 -412.7239) 
(list 4553.585 -412.8) 
(list 4480.0675 -412.8) 
(list 4480.0675 -410.8) 
(list 4479.9325 -410.8) 
(list 4479.9325 -412.8) 
(list 4406.415 -412.8) 
(list 4406.0323 -412.7239) 
(list 4405.7079 -412.5071) 
(list 4405.4911 -412.1827) 
(list 4405.415 -411.8) 
(list 4405.415 -411.8) 
(list 4405.415 -414) 
(list 4405.4911 -413.6173) 
(list 4405.7079 -413.2929) 
(list 4406.0323 -413.0761) 
(list 4406.415 -413) 
(list 4406.415 -413) 
(list 4479.9325 -413) 
(list 4479.9325 -415)))
(apply 'command (append '("pline") coords '("c")))
(setq currobj (ssadd (entlast) currobj))
(command "._fillet" "radius" "0.3" "._fillet" "P" (entlast))
(command "_layer" "set" "holes" "")
(command "_circle" "4480,-412.9" "0.113")
(setq currobj (ssadd (entlast) currobj))
(command "_layer" "set" "nitride" "")
(command "_layer" "set" "text" "")
(command "_circle" "4479.2,-415" "0.075")
(command "_circle" "4479.2,-414.7" "0.075")
(command "_circle" "4479.2,-414.4" "0.075")
(command "_circle" "4478.9,-415" "0.075")
(command "_circle" "4478.9,-414.7" "0.075")
(command "_circle" "4478.9,-414.4" "0.075")
(command "_circle" "4478.6,-415" "0.075")
(command "_circle" "4478.6,-414.7" "0.075")
(command "_circle" "4478.6,-414.4" "0.075")
(command "_layer" "set" "nitride" "")
(command "_layer" "set" "prebias" "")
(command "_rectangle" "4405.415,-414" "4554.585,-411.8")
(setq currobj (ssadd (entlast) currobj))
(command "_rectangle" "4479.9325,-415" "4480.0675,-410.8")
(setq currobj (ssadd (entlast) currobj))
(command "_layer" "set" "nitride" "")
(setq coupler14 currobj)
(setq currobj nil)
(setq currobj (ssadd))
; DRAWING SINGLE NANOBEAM
(setq coords (list 
(list 4480.0675 -410.8) 
(list 4480.0675 -409.1417) 
(list 4480.0675 -407.4833) 
(list 4480.0675 -405.825) 
(list 4480.0675 -404.1667) 
(list 4480.0675 -402.5083) 
(list 4480.0675 -400.85) 
(list 4480.0675 -399.1917) 
(list 4480.0675 -397.5333) 
(list 4480.0675 -395.875) 
(list 4480.0676 -394.2167) 
(list 4480.0676 -392.5583) 
(list 4480.0676 -390.9) 
(list 4480.0676 -389.2417) 
(list 4480.0677 -387.5833) 
(list 4480.0677 -385.925) 
(list 4480.0678 -384.2667) 
(list 4480.0678 -382.6083) 
(list 4480.0679 -380.95) 
(list 4480.068 -379.2917) 
(list 4480.068 -377.6333) 
(list 4480.0681 -375.975) 
(list 4480.0682 -374.3167) 
(list 4480.0683 -372.6583) 
(list 4480.0684 -371) 
(list 4480.0686 -369.3417) 
(list 4480.0687 -367.6833) 
(list 4480.0688 -366.025) 
(list 4480.069 -364.3667) 
(list 4480.0692 -362.7083) 
(list 4480.0693 -361.05) 
(list 4480.0695 -359.3917) 
(list 4480.0697 -357.7333) 
(list 4480.0699 -356.075) 
(list 4480.0702 -354.4167) 
(list 4480.0704 -352.7583) 
(list 4480.0707 -351.1) 
(list 4480.0709 -349.4417) 
(list 4480.0712 -347.7833) 
(list 4480.0715 -346.125) 
(list 4480.0719 -344.4667) 
(list 4480.0722 -342.8083) 
(list 4480.0725 -341.15) 
(list 4480.0729 -339.4917) 
(list 4480.0733 -337.8333) 
(list 4480.0737 -336.175) 
(list 4480.0741 -334.5167) 
(list 4480.0746 -332.8583) 
(list 4480.075 -331.2) 
(list 4480.0755 -329.5417) 
(list 4480.076 -327.8833) 
(list 4480.0765 -326.225) 
(list 4480.0771 -324.5667) 
(list 4480.0776 -322.9083) 
(list 4480.0782 -321.25) 
(list 4480.0788 -319.5917) 
(list 4480.0794 -317.9333) 
(list 4480.0801 -316.275) 
(list 4480.0808 -314.6167) 
(list 4480.0815 -312.9583) 
(list 4480.0822 -311.3) 
(list 4480.0829 -309.6417) 
(list 4480.0837 -307.9833) 
(list 4480.0845 -306.325) 
(list 4480.0853 -304.6667) 
(list 4480.0862 -303.0083) 
(list 4480.087 -301.35) 
(list 4480.088 -299.6917) 
(list 4480.0889 -298.0333) 
(list 4480.0898 -296.375) 
(list 4480.0908 -294.7167) 
(list 4480.0918 -293.0583) 
(list 4480.0929 -291.4) 
(list 4480.094 -289.7417) 
(list 4480.0951 -288.0833) 
(list 4480.0962 -286.425) 
(list 4480.0973 -284.7667) 
(list 4480.0985 -283.1083) 
(list 4480.0998 -281.45) 
(list 4480.101 -279.7917) 
(list 4480.1023 -278.1333) 
(list 4480.1036 -276.475) 
(list 4480.105 -274.8167) 
(list 4480.1064 -273.1583) 
(list 4480.1078 -271.5) 
(list 4480.1093 -269.8417) 
(list 4480.1107 -268.1833) 
(list 4480.1123 -266.525) 
(list 4480.1138 -264.8667) 
(list 4480.1154 -263.2083) 
(list 4480.1171 -261.55) 
(list 4480.1187 -259.8917) 
(list 4480.1204 -258.2333) 
(list 4480.1222 -256.575) 
(list 4480.124 -254.9167) 
(list 4480.1258 -253.2583) 
(list 4480.1277 -251.6) 
(list 4480.1296 -249.9417) 
(list 4480.1315 -248.2833) 
(list 4480.1335 -246.625) 
(list 4480.1355 -244.9667) 
(list 4480.1376 -243.3083) 
(list 4480.1397 -241.65) 
(list 4480.1418 -239.9917) 
(list 4480.144 -238.3333) 
(list 4480.1462 -236.675) 
(list 4480.1485 -235.0167) 
(list 4480.1508 -233.3583) 
(list 4480.1532 -231.7) 
(list 4480.1556 -230.0417) 
(list 4480.158 -228.3833) 
(list 4480.1605 -226.725) 
(list 4480.163 -225.0667) 
(list 4480.1656 -223.4083) 
(list 4480.1682 -221.75) 
(list 4480.1709 -220.0917) 
(list 4480.1736 -218.4333) 
(list 4480.1764 -216.775) 
(list 4480.1792 -215.1167) 
(list 4480.1821 -213.4583) 
(list 4480.185 -211.8) 
(list 4479.815 -211.8) 
(list 4479.8179 -213.4583) 
(list 4479.8208 -215.1167) 
(list 4479.8236 -216.775) 
(list 4479.8264 -218.4333) 
(list 4479.8291 -220.0917) 
(list 4479.8318 -221.75) 
(list 4479.8344 -223.4083) 
(list 4479.837 -225.0667) 
(list 4479.8395 -226.725) 
(list 4479.842 -228.3833) 
(list 4479.8444 -230.0417) 
(list 4479.8468 -231.7) 
(list 4479.8492 -233.3583) 
(list 4479.8515 -235.0167) 
(list 4479.8538 -236.675) 
(list 4479.856 -238.3333) 
(list 4479.8582 -239.9917) 
(list 4479.8603 -241.65) 
(list 4479.8624 -243.3083) 
(list 4479.8645 -244.9667) 
(list 4479.8665 -246.625) 
(list 4479.8685 -248.2833) 
(list 4479.8704 -249.9417) 
(list 4479.8723 -251.6) 
(list 4479.8742 -253.2583) 
(list 4479.876 -254.9167) 
(list 4479.8778 -256.575) 
(list 4479.8796 -258.2333) 
(list 4479.8813 -259.8917) 
(list 4479.8829 -261.55) 
(list 4479.8846 -263.2083) 
(list 4479.8862 -264.8667) 
(list 4479.8877 -266.525) 
(list 4479.8893 -268.1833) 
(list 4479.8907 -269.8417) 
(list 4479.8922 -271.5) 
(list 4479.8936 -273.1583) 
(list 4479.895 -274.8167) 
(list 4479.8964 -276.475) 
(list 4479.8977 -278.1333) 
(list 4479.899 -279.7917) 
(list 4479.9002 -281.45) 
(list 4479.9015 -283.1083) 
(list 4479.9027 -284.7667) 
(list 4479.9038 -286.425) 
(list 4479.9049 -288.0833) 
(list 4479.906 -289.7417) 
(list 4479.9071 -291.4) 
(list 4479.9082 -293.0583) 
(list 4479.9092 -294.7167) 
(list 4479.9102 -296.375) 
(list 4479.9111 -298.0333) 
(list 4479.912 -299.6917) 
(list 4479.913 -301.35) 
(list 4479.9138 -303.0083) 
(list 4479.9147 -304.6667) 
(list 4479.9155 -306.325) 
(list 4479.9163 -307.9833) 
(list 4479.9171 -309.6417) 
(list 4479.9178 -311.3) 
(list 4479.9185 -312.9583) 
(list 4479.9192 -314.6167) 
(list 4479.9199 -316.275) 
(list 4479.9206 -317.9333) 
(list 4479.9212 -319.5917) 
(list 4479.9218 -321.25) 
(list 4479.9224 -322.9083) 
(list 4479.9229 -324.5667) 
(list 4479.9235 -326.225) 
(list 4479.924 -327.8833) 
(list 4479.9245 -329.5417) 
(list 4479.925 -331.2) 
(list 4479.9254 -332.8583) 
(list 4479.9259 -334.5167) 
(list 4479.9263 -336.175) 
(list 4479.9267 -337.8333) 
(list 4479.9271 -339.4917) 
(list 4479.9275 -341.15) 
(list 4479.9278 -342.8083) 
(list 4479.9281 -344.4667) 
(list 4479.9285 -346.125) 
(list 4479.9288 -347.7833) 
(list 4479.9291 -349.4417) 
(list 4479.9293 -351.1) 
(list 4479.9296 -352.7583) 
(list 4479.9298 -354.4167) 
(list 4479.9301 -356.075) 
(list 4479.9303 -357.7333) 
(list 4479.9305 -359.3917) 
(list 4479.9307 -361.05) 
(list 4479.9308 -362.7083) 
(list 4479.931 -364.3667) 
(list 4479.9312 -366.025) 
(list 4479.9313 -367.6833) 
(list 4479.9314 -369.3417) 
(list 4479.9316 -371) 
(list 4479.9317 -372.6583) 
(list 4479.9318 -374.3167) 
(list 4479.9319 -375.975) 
(list 4479.932 -377.6333) 
(list 4479.932 -379.2917) 
(list 4479.9321 -380.95) 
(list 4479.9322 -382.6083) 
(list 4479.9322 -384.2667) 
(list 4479.9323 -385.925) 
(list 4479.9323 -387.5833) 
(list 4479.9324 -389.2417) 
(list 4479.9324 -390.9) 
(list 4479.9324 -392.5583) 
(list 4479.9324 -394.2167) 
(list 4479.9325 -395.875) 
(list 4479.9325 -397.5333) 
(list 4479.9325 -399.1917) 
(list 4479.9325 -400.85) 
(list 4479.9325 -402.5083) 
(list 4479.9325 -404.1667) 
(list 4479.9325 -405.825) 
(list 4479.9325 -407.4833) 
(list 4479.9325 -409.1417) 
(list 4479.9325 -410.8)))
(apply 'command (append '("pline") coords '("c")))
(setq currobj (ssadd (entlast) currobj))
(command "_layer" "set" "prebias" "")
(command "_rectangle" "4479.815,-410.8" "4480.185,-211.8")
(setq currobj (ssadd (entlast) currobj))
(command "_layer" "set" "nitride" "")
(setq singlenanobeam14 currobj)
(setq currobj nil)
(setq currobj (ssadd))
; DRAWING NODE ARRAY
(setq coords (list 
(list 4480.185 -211.8) 
(list 4480.5625 -201.8) 
(list 4480.5625 -201.8) 
(list 4480.5625 -200.8) 
(list 4554.585 -212.6864) 
(list 4554.585 -207.7434) 
(list 4480.5625 -197.357) 
(list 4480.5625 -196.357) 
(list 4480.5625 -196.357) 
(list 4480.2625 -186.357) 
(list 4479.7375 -186.357) 
(list 4479.4375 -196.357) 
(list 4479.4375 -196.357) 
(list 4479.4375 -197.357) 
(list 4405.415 -207.7434) 
(list 4405.415 -212.6864) 
(list 4479.4375 -200.8) 
(list 4479.4375 -201.8) 
(list 4479.4375 -201.8) 
(list 4479.815 -211.8)))
(apply 'command (append '("pline") coords '("c")))
(setq currobj (ssadd (entlast) currobj))
(command "_layer" "set" "prebias" "")
(setq coords (list 
(list 4479.4375 -212.6864) 
(list 4479.4375 -200.8) 
(list 4405.415 -212.6864) 
(list 4405.415 -207.7434) 
(list 4479.4375 -197.357) 
(list 4479.4375 -186.357) 
(list 4480.5625 -186.357) 
(list 4480.5625 -197.357) 
(list 4554.585 -207.7434) 
(list 4554.585 -212.6864) 
(list 4480.5625 -200.8) 
(list 4480.5625 -212.6864)))
(apply 'command (append '("pline") coords '("c")))
(setq currobj (ssadd (entlast) currobj))
(command "_layer" "set" "nitride" "")
(command "_layer" "set" "fda1" "")
(setq coords (list 
(list 4480.5625 -200.657) 
(list 4554.585 -212.5434) 
(list 4554.585 -212.3664) 
(list 4480.5625 -200.58)))
(apply 'command (append '("pline") coords '("c")))
(setq currobj (ssadd (entlast) currobj))
(setq coords (list 
(list 4480.5625 -200.437) 
(list 4554.585 -212.2234) 
(list 4554.585 -212.0464) 
(list 4480.5625 -200.36)))
(apply 'command (append '("pline") coords '("c")))
(setq currobj (ssadd (entlast) currobj))
(setq coords (list 
(list 4480.5625 -200.217) 
(list 4554.585 -211.9034) 
(list 4554.585 -211.7264) 
(list 4480.5625 -200.14)))
(apply 'command (append '("pline") coords '("c")))
(setq currobj (ssadd (entlast) currobj))
(setq coords (list 
(list 4480.5625 -199.997) 
(list 4554.585 -211.5834) 
(list 4554.585 -211.4064) 
(list 4480.5625 -199.92)))
(apply 'command (append '("pline") coords '("c")))
(setq currobj (ssadd (entlast) currobj))
(setq coords (list 
(list 4480.5625 -199.777) 
(list 4554.585 -211.2634) 
(list 4554.585 -211.0864) 
(list 4480.5625 -199.7)))
(apply 'command (append '("pline") coords '("c")))
(setq currobj (ssadd (entlast) currobj))
(setq coords (list 
(list 4480.5625 -199.557) 
(list 4554.585 -210.9434) 
(list 4554.585 -210.7664) 
(list 4480.5625 -199.48)))
(apply 'command (append '("pline") coords '("c")))
(setq currobj (ssadd (entlast) currobj))
(setq coords (list 
(list 4480.5625 -199.337) 
(list 4554.585 -210.6234) 
(list 4554.585 -210.4464) 
(list 4480.5625 -199.26)))
(apply 'command (append '("pline") coords '("c")))
(setq currobj (ssadd (entlast) currobj))
(setq coords (list 
(list 4480.5625 -199.117) 
(list 4554.585 -210.3034) 
(list 4554.585 -210.1264) 
(list 4480.5625 -199.04)))
(apply 'command (append '("pline") coords '("c")))
(setq currobj (ssadd (entlast) currobj))
(setq coords (list 
(list 4480.5625 -198.897) 
(list 4554.585 -209.9834) 
(list 4554.585 -209.8064) 
(list 4480.5625 -198.82)))
(apply 'command (append '("pline") coords '("c")))
(setq currobj (ssadd (entlast) currobj))
(setq coords (list 
(list 4480.5625 -198.677) 
(list 4554.585 -209.6634) 
(list 4554.585 -209.4864) 
(list 4480.5625 -198.6)))
(apply 'command (append '("pline") coords '("c")))
(setq currobj (ssadd (entlast) currobj))
(setq coords (list 
(list 4480.5625 -198.457) 
(list 4554.585 -209.3434) 
(list 4554.585 -209.1664) 
(list 4480.5625 -198.38)))
(apply 'command (append '("pline") coords '("c")))
(setq currobj (ssadd (entlast) currobj))
(setq coords (list 
(list 4480.5625 -198.237) 
(list 4554.585 -209.0234) 
(list 4554.585 -208.8464) 
(list 4480.5625 -198.16)))
(apply 'command (append '("pline") coords '("c")))
(setq currobj (ssadd (entlast) currobj))
(setq coords (list 
(list 4480.5625 -198.017) 
(list 4554.585 -208.7034) 
(list 4554.585 -208.5264) 
(list 4480.5625 -197.94)))
(apply 'command (append '("pline") coords '("c")))
(setq currobj (ssadd (entlast) currobj))
(setq coords (list 
(list 4480.5625 -197.797) 
(list 4554.585 -208.3834) 
(list 4554.585 -208.2064) 
(list 4480.5625 -197.72)))
(apply 'command (append '("pline") coords '("c")))
(setq currobj (ssadd (entlast) currobj))
(setq coords (list 
(list 4480.5625 -197.577) 
(list 4554.585 -208.0634) 
(list 4554.585 -207.8864) 
(list 4480.5625 -197.5)))
(apply 'command (append '("pline") coords '("c")))
(setq currobj (ssadd (entlast) currobj))
(setq coords (list 
(list 4479.4375 -197.5) 
(list 4405.415 -207.8864) 
(list 4405.415 -208.0634) 
(list 4479.4375 -197.577)))
(apply 'command (append '("pline") coords '("c")))
(setq currobj (ssadd (entlast) currobj))
(setq coords (list 
(list 4479.4375 -197.72) 
(list 4405.415 -208.2064) 
(list 4405.415 -208.3834) 
(list 4479.4375 -197.797)))
(apply 'command (append '("pline") coords '("c")))
(setq currobj (ssadd (entlast) currobj))
(setq coords (list 
(list 4479.4375 -197.94) 
(list 4405.415 -208.5264) 
(list 4405.415 -208.7034) 
(list 4479.4375 -198.017)))
(apply 'command (append '("pline") coords '("c")))
(setq currobj (ssadd (entlast) currobj))
(setq coords (list 
(list 4479.4375 -198.16) 
(list 4405.415 -208.8464) 
(list 4405.415 -209.0234) 
(list 4479.4375 -198.237)))
(apply 'command (append '("pline") coords '("c")))
(setq currobj (ssadd (entlast) currobj))
(setq coords (list 
(list 4479.4375 -198.38) 
(list 4405.415 -209.1664) 
(list 4405.415 -209.3434) 
(list 4479.4375 -198.457)))
(apply 'command (append '("pline") coords '("c")))
(setq currobj (ssadd (entlast) currobj))
(setq coords (list 
(list 4479.4375 -198.6) 
(list 4405.415 -209.4864) 
(list 4405.415 -209.6634) 
(list 4479.4375 -198.677)))
(apply 'command (append '("pline") coords '("c")))
(setq currobj (ssadd (entlast) currobj))
(setq coords (list 
(list 4479.4375 -198.82) 
(list 4405.415 -209.8064) 
(list 4405.415 -209.9834) 
(list 4479.4375 -198.897)))
(apply 'command (append '("pline") coords '("c")))
(setq currobj (ssadd (entlast) currobj))
(setq coords (list 
(list 4479.4375 -199.04) 
(list 4405.415 -210.1264) 
(list 4405.415 -210.3034) 
(list 4479.4375 -199.117)))
(apply 'command (append '("pline") coords '("c")))
(setq currobj (ssadd (entlast) currobj))
(setq coords (list 
(list 4479.4375 -199.26) 
(list 4405.415 -210.4464) 
(list 4405.415 -210.6234) 
(list 4479.4375 -199.337)))
(apply 'command (append '("pline") coords '("c")))
(setq currobj (ssadd (entlast) currobj))
(setq coords (list 
(list 4479.4375 -199.48) 
(list 4405.415 -210.7664) 
(list 4405.415 -210.9434) 
(list 4479.4375 -199.557)))
(apply 'command (append '("pline") coords '("c")))
(setq currobj (ssadd (entlast) currobj))
(setq coords (list 
(list 4479.4375 -199.7) 
(list 4405.415 -211.0864) 
(list 4405.415 -211.2634) 
(list 4479.4375 -199.777)))
(apply 'command (append '("pline") coords '("c")))
(setq currobj (ssadd (entlast) currobj))
(setq coords (list 
(list 4479.4375 -199.92) 
(list 4405.415 -211.4064) 
(list 4405.415 -211.5834) 
(list 4479.4375 -199.997)))
(apply 'command (append '("pline") coords '("c")))
(setq currobj (ssadd (entlast) currobj))
(setq coords (list 
(list 4479.4375 -200.14) 
(list 4405.415 -211.7264) 
(list 4405.415 -211.9034) 
(list 4479.4375 -200.217)))
(apply 'command (append '("pline") coords '("c")))
(setq currobj (ssadd (entlast) currobj))
(setq coords (list 
(list 4479.4375 -200.36) 
(list 4405.415 -212.0464) 
(list 4405.415 -212.2234) 
(list 4479.4375 -200.437)))
(apply 'command (append '("pline") coords '("c")))
(setq currobj (ssadd (entlast) currobj))
(setq coords (list 
(list 4479.4375 -200.58) 
(list 4405.415 -212.3664) 
(list 4405.415 -212.5434) 
(list 4479.4375 -200.657)))
(apply 'command (append '("pline") coords '("c")))
(setq currobj (ssadd (entlast) currobj))
(command "_layer" "set" "nitride" "")
(command "_layer" "set" "text" "")
(command "_circle" "4478.985,-211.8" "0.075")
(command "_circle" "4478.985,-211.5" "0.075")
(command "_circle" "4478.985,-211.2" "0.075")
(command "_circle" "4478.985,-210.9" "0.075")
(command "_circle" "4478.985,-210.6" "0.075")
(command "_circle" "4478.685,-211.8" "0.075")
(command "_circle" "4478.685,-211.5" "0.075")
(command "_circle" "4478.685,-211.2" "0.075")
(command "_circle" "4478.685,-210.9" "0.075")
(command "_circle" "4478.685,-210.6" "0.075")
(command "_circle" "4478.385,-211.8" "0.075")
(command "_circle" "4478.385,-211.5" "0.075")
(command "_circle" "4478.385,-211.2" "0.075")
(command "_circle" "4478.385,-210.9" "0.075")
(command "_circle" "4478.385,-210.6" "0.075")
(command "_circle" "4478.085,-211.8" "0.075")
(command "_circle" "4478.085,-211.5" "0.075")
(command "_circle" "4478.085,-211.2" "0.075")
(command "_circle" "4478.085,-210.9" "0.075")
(command "_circle" "4478.085,-210.6" "0.075")
(command "_circle" "4477.785,-211.8" "0.075")
(command "_circle" "4477.785,-211.5" "0.075")
(command "_circle" "4477.785,-211.2" "0.075")
(command "_circle" "4477.785,-210.9" "0.075")
(command "_circle" "4477.785,-210.6" "0.075")
(command "_layer" "set" "nitride" "")
(setq anglednodearray14 currobj)
(setq currobj nil)
(setq currobj (ssadd))
; DRAWING COOLED SINGLE NANOBEAM
(setq coords (list 
(list 4480.2625 -186.357) 
(list 4480.2625 -181.357) 
(list 4479.7375 -181.357) 
(list 4479.7375 -186.357)))
(apply 'command (append '("pline") coords '("c")))
(setq currobj (ssadd (entlast) currobj))
(command "_layer" "set" "prebias" "")
(command "_rectangle" "4479.7375,-186.357" "4480.2625,-181.357")
(setq currobj (ssadd (entlast) currobj))
(command "_layer" "set" "nitride" "")
(setq coords (list 
(list 4480.2625 -181.357) 
(list 4480.5625 -171.357) 
(list 4480.5625 -171.357) 
(list 4480.5625 -170.357) 
(list 4554.585 -171.107) 
(list 4554.585 -166.164) 
(list 4480.5625 -166.914) 
(list 4480.5625 -165.914) 
(list 4480.5625 -165.914) 
(list 4480.2625 -155.914) 
(list 4479.7375 -155.914) 
(list 4479.4375 -165.914) 
(list 4479.4375 -165.914) 
(list 4479.4375 -166.914) 
(list 4405.415 -166.164) 
(list 4405.415 -171.107) 
(list 4479.4375 -170.357) 
(list 4479.4375 -171.357) 
(list 4479.4375 -171.357) 
(list 4479.7375 -181.357)))
(apply 'command (append '("pline") coords '("c")))
(setq currobj (ssadd (entlast) currobj))
(command "_layer" "set" "prebias" "")
(setq coords (list 
(list 4479.4375 -181.357) 
(list 4479.4375 -170.357) 
(list 4405.415 -171.107) 
(list 4405.415 -166.164) 
(list 4479.4375 -166.914) 
(list 4479.4375 -155.914) 
(list 4480.5625 -155.914) 
(list 4480.5625 -166.914) 
(list 4554.585 -166.164) 
(list 4554.585 -171.107) 
(list 4480.5625 -170.357) 
(list 4480.5625 -181.357)))
(apply 'command (append '("pline") coords '("c")))
(setq currobj (ssadd (entlast) currobj))
(command "_layer" "set" "nitride" "")
(command "_layer" "set" "fda1" "")
(setq coords (list 
(list 4480.5625 -170.214) 
(list 4554.585 -170.964) 
(list 4554.585 -170.787) 
(list 4480.5625 -170.137)))
(apply 'command (append '("pline") coords '("c")))
(setq currobj (ssadd (entlast) currobj))
(setq coords (list 
(list 4480.5625 -169.994) 
(list 4554.585 -170.644) 
(list 4554.585 -170.467) 
(list 4480.5625 -169.917)))
(apply 'command (append '("pline") coords '("c")))
(setq currobj (ssadd (entlast) currobj))
(setq coords (list 
(list 4480.5625 -169.774) 
(list 4554.585 -170.324) 
(list 4554.585 -170.147) 
(list 4480.5625 -169.697)))
(apply 'command (append '("pline") coords '("c")))
(setq currobj (ssadd (entlast) currobj))
(setq coords (list 
(list 4480.5625 -169.554) 
(list 4554.585 -170.004) 
(list 4554.585 -169.827) 
(list 4480.5625 -169.477)))
(apply 'command (append '("pline") coords '("c")))
(setq currobj (ssadd (entlast) currobj))
(setq coords (list 
(list 4480.5625 -169.334) 
(list 4554.585 -169.684) 
(list 4554.585 -169.507) 
(list 4480.5625 -169.257)))
(apply 'command (append '("pline") coords '("c")))
(setq currobj (ssadd (entlast) currobj))
(setq coords (list 
(list 4480.5625 -169.114) 
(list 4554.585 -169.364) 
(list 4554.585 -169.187) 
(list 4480.5625 -169.037)))
(apply 'command (append '("pline") coords '("c")))
(setq currobj (ssadd (entlast) currobj))
(setq coords (list 
(list 4480.5625 -168.894) 
(list 4554.585 -169.044) 
(list 4554.585 -168.867) 
(list 4480.5625 -168.817)))
(apply 'command (append '("pline") coords '("c")))
(setq currobj (ssadd (entlast) currobj))
(setq coords (list 
(list 4480.5625 -168.674) 
(list 4554.585 -168.724) 
(list 4554.585 -168.547) 
(list 4480.5625 -168.597)))
(apply 'command (append '("pline") coords '("c")))
(setq currobj (ssadd (entlast) currobj))
(setq coords (list 
(list 4480.5625 -168.454) 
(list 4554.585 -168.404) 
(list 4554.585 -168.227) 
(list 4480.5625 -168.377)))
(apply 'command (append '("pline") coords '("c")))
(setq currobj (ssadd (entlast) currobj))
(setq coords (list 
(list 4480.5625 -168.234) 
(list 4554.585 -168.084) 
(list 4554.585 -167.907) 
(list 4480.5625 -168.157)))
(apply 'command (append '("pline") coords '("c")))
(setq currobj (ssadd (entlast) currobj))
(setq coords (list 
(list 4480.5625 -168.014) 
(list 4554.585 -167.764) 
(list 4554.585 -167.587) 
(list 4480.5625 -167.937)))
(apply 'command (append '("pline") coords '("c")))
(setq currobj (ssadd (entlast) currobj))
(setq coords (list 
(list 4480.5625 -167.794) 
(list 4554.585 -167.444) 
(list 4554.585 -167.267) 
(list 4480.5625 -167.717)))
(apply 'command (append '("pline") coords '("c")))
(setq currobj (ssadd (entlast) currobj))
(setq coords (list 
(list 4480.5625 -167.574) 
(list 4554.585 -167.124) 
(list 4554.585 -166.947) 
(list 4480.5625 -167.497)))
(apply 'command (append '("pline") coords '("c")))
(setq currobj (ssadd (entlast) currobj))
(setq coords (list 
(list 4480.5625 -167.354) 
(list 4554.585 -166.804) 
(list 4554.585 -166.627) 
(list 4480.5625 -167.277)))
(apply 'command (append '("pline") coords '("c")))
(setq currobj (ssadd (entlast) currobj))
(setq coords (list 
(list 4480.5625 -167.134) 
(list 4554.585 -166.484) 
(list 4554.585 -166.307) 
(list 4480.5625 -167.057)))
(apply 'command (append '("pline") coords '("c")))
(setq currobj (ssadd (entlast) currobj))
(setq coords (list 
(list 4479.4375 -167.057) 
(list 4405.415 -166.307) 
(list 4405.415 -166.484) 
(list 4479.4375 -167.134)))
(apply 'command (append '("pline") coords '("c")))
(setq currobj (ssadd (entlast) currobj))
(setq coords (list 
(list 4479.4375 -167.277) 
(list 4405.415 -166.627) 
(list 4405.415 -166.804) 
(list 4479.4375 -167.354)))
(apply 'command (append '("pline") coords '("c")))
(setq currobj (ssadd (entlast) currobj))
(setq coords (list 
(list 4479.4375 -167.497) 
(list 4405.415 -166.947) 
(list 4405.415 -167.124) 
(list 4479.4375 -167.574)))
(apply 'command (append '("pline") coords '("c")))
(setq currobj (ssadd (entlast) currobj))
(setq coords (list 
(list 4479.4375 -167.717) 
(list 4405.415 -167.267) 
(list 4405.415 -167.444) 
(list 4479.4375 -167.794)))
(apply 'command (append '("pline") coords '("c")))
(setq currobj (ssadd (entlast) currobj))
(setq coords (list 
(list 4479.4375 -167.937) 
(list 4405.415 -167.587) 
(list 4405.415 -167.764) 
(list 4479.4375 -168.014)))
(apply 'command (append '("pline") coords '("c")))
(setq currobj (ssadd (entlast) currobj))
(setq coords (list 
(list 4479.4375 -168.157) 
(list 4405.415 -167.907) 
(list 4405.415 -168.084) 
(list 4479.4375 -168.234)))
(apply 'command (append '("pline") coords '("c")))
(setq currobj (ssadd (entlast) currobj))
(setq coords (list 
(list 4479.4375 -168.377) 
(list 4405.415 -168.227) 
(list 4405.415 -168.404) 
(list 4479.4375 -168.454)))
(apply 'command (append '("pline") coords '("c")))
(setq currobj (ssadd (entlast) currobj))
(setq coords (list 
(list 4479.4375 -168.597) 
(list 4405.415 -168.547) 
(list 4405.415 -168.724) 
(list 4479.4375 -168.674)))
(apply 'command (append '("pline") coords '("c")))
(setq currobj (ssadd (entlast) currobj))
(setq coords (list 
(list 4479.4375 -168.817) 
(list 4405.415 -168.867) 
(list 4405.415 -169.044) 
(list 4479.4375 -168.894)))
(apply 'command (append '("pline") coords '("c")))
(setq currobj (ssadd (entlast) currobj))
(setq coords (list 
(list 4479.4375 -169.037) 
(list 4405.415 -169.187) 
(list 4405.415 -169.364) 
(list 4479.4375 -169.114)))
(apply 'command (append '("pline") coords '("c")))
(setq currobj (ssadd (entlast) currobj))
(setq coords (list 
(list 4479.4375 -169.257) 
(list 4405.415 -169.507) 
(list 4405.415 -169.684) 
(list 4479.4375 -169.334)))
(apply 'command (append '("pline") coords '("c")))
(setq currobj (ssadd (entlast) currobj))
(setq coords (list 
(list 4479.4375 -169.477) 
(list 4405.415 -169.827) 
(list 4405.415 -170.004) 
(list 4479.4375 -169.554)))
(apply 'command (append '("pline") coords '("c")))
(setq currobj (ssadd (entlast) currobj))
(setq coords (list 
(list 4479.4375 -169.697) 
(list 4405.415 -170.147) 
(list 4405.415 -170.324) 
(list 4479.4375 -169.774)))
(apply 'command (append '("pline") coords '("c")))
(setq currobj (ssadd (entlast) currobj))
(setq coords (list 
(list 4479.4375 -169.917) 
(list 4405.415 -170.467) 
(list 4405.415 -170.644) 
(list 4479.4375 -169.994)))
(apply 'command (append '("pline") coords '("c")))
(setq currobj (ssadd (entlast) currobj))
(setq coords (list 
(list 4479.4375 -170.137) 
(list 4405.415 -170.787) 
(list 4405.415 -170.964) 
(list 4479.4375 -170.214)))
(apply 'command (append '("pline") coords '("c")))
(setq currobj (ssadd (entlast) currobj))
(command "_layer" "set" "nitride" "")
(command "_layer" "set" "text" "")
(command "_circle" "4479.0625,-181.357" "0.075")
(command "_circle" "4479.0625,-181.057" "0.075")
(command "_circle" "4479.0625,-180.757" "0.075")
(command "_circle" "4479.0625,-180.457" "0.075")
(command "_circle" "4479.0625,-180.157" "0.075")
(command "_circle" "4478.7625,-181.357" "0.075")
(command "_circle" "4478.7625,-181.057" "0.075")
(command "_circle" "4478.7625,-180.757" "0.075")
(command "_circle" "4478.7625,-180.457" "0.075")
(command "_circle" "4478.7625,-180.157" "0.075")
(command "_circle" "4478.4625,-181.357" "0.075")
(command "_circle" "4478.4625,-181.057" "0.075")
(command "_circle" "4478.4625,-180.757" "0.075")
(command "_circle" "4478.4625,-180.457" "0.075")
(command "_circle" "4478.4625,-180.157" "0.075")
(command "_circle" "4478.1625,-181.357" "0.075")
(command "_circle" "4478.1625,-181.057" "0.075")
(command "_circle" "4478.1625,-180.757" "0.075")
(command "_circle" "4478.1625,-180.457" "0.075")
(command "_circle" "4478.1625,-180.157" "0.075")
(command "_circle" "4477.8625,-181.357" "0.075")
(command "_circle" "4477.8625,-181.057" "0.075")
(command "_circle" "4477.8625,-180.757" "0.075")
(command "_circle" "4477.8625,-180.457" "0.075")
(command "_circle" "4477.8625,-180.157" "0.075")
(command "_layer" "set" "nitride" "")
(setq coords (list 
(list 4480.2625 -155.914) 
(list 4480.2625 -40.2693) 
(list 4479.7375 -40.2693) 
(list 4479.7375 -155.914)))
(apply 'command (append '("pline") coords '("c")))
(setq currobj (ssadd (entlast) currobj))
(command "_layer" "set" "prebias" "")
(command "_rectangle" "4479.7375,-155.914" "4480.2625,-40.2693")
(setq currobj (ssadd (entlast) currobj))
(command "_layer" "set" "nitride" "")
(setq coords (list 
(list 4480.2625 -40.2693) 
(list 4480.5625 -30.2693) 
(list 4480.5625 -30.2693) 
(list 4480.5625 -29.2693) 
(list 4554.585 -30.0193) 
(list 4554.585 -25.0763) 
(list 4480.5625 -25.8263) 
(list 4480.5625 -24.8263) 
(list 4480.5625 -24.8263) 
(list 4480.2625 -14.8263) 
(list 4479.7375 -14.8263) 
(list 4479.4375 -24.8263) 
(list 4479.4375 -24.8263) 
(list 4479.4375 -25.8263) 
(list 4405.415 -25.0763) 
(list 4405.415 -30.0193) 
(list 4479.4375 -29.2693) 
(list 4479.4375 -30.2693) 
(list 4479.4375 -30.2693) 
(list 4479.7375 -40.2693)))
(apply 'command (append '("pline") coords '("c")))
(setq currobj (ssadd (entlast) currobj))
(command "_layer" "set" "prebias" "")
(setq coords (list 
(list 4479.4375 -40.2693) 
(list 4479.4375 -29.2693) 
(list 4405.415 -30.0193) 
(list 4405.415 -25.0763) 
(list 4479.4375 -25.8263) 
(list 4479.4375 -14.8263) 
(list 4480.5625 -14.8263) 
(list 4480.5625 -25.8263) 
(list 4554.585 -25.0763) 
(list 4554.585 -30.0193) 
(list 4480.5625 -29.2693) 
(list 4480.5625 -40.2693)))
(apply 'command (append '("pline") coords '("c")))
(setq currobj (ssadd (entlast) currobj))
(command "_layer" "set" "nitride" "")
(command "_layer" "set" "fda1" "")
(setq coords (list 
(list 4480.5625 -29.1263) 
(list 4554.585 -29.8763) 
(list 4554.585 -29.6993) 
(list 4480.5625 -29.0493)))
(apply 'command (append '("pline") coords '("c")))
(setq currobj (ssadd (entlast) currobj))
(setq coords (list 
(list 4480.5625 -28.9063) 
(list 4554.585 -29.5563) 
(list 4554.585 -29.3793) 
(list 4480.5625 -28.8293)))
(apply 'command (append '("pline") coords '("c")))
(setq currobj (ssadd (entlast) currobj))
(setq coords (list 
(list 4480.5625 -28.6863) 
(list 4554.585 -29.2363) 
(list 4554.585 -29.0593) 
(list 4480.5625 -28.6093)))
(apply 'command (append '("pline") coords '("c")))
(setq currobj (ssadd (entlast) currobj))
(setq coords (list 
(list 4480.5625 -28.4663) 
(list 4554.585 -28.9163) 
(list 4554.585 -28.7393) 
(list 4480.5625 -28.3893)))
(apply 'command (append '("pline") coords '("c")))
(setq currobj (ssadd (entlast) currobj))
(setq coords (list 
(list 4480.5625 -28.2463) 
(list 4554.585 -28.5963) 
(list 4554.585 -28.4193) 
(list 4480.5625 -28.1693)))
(apply 'command (append '("pline") coords '("c")))
(setq currobj (ssadd (entlast) currobj))
(setq coords (list 
(list 4480.5625 -28.0263) 
(list 4554.585 -28.2763) 
(list 4554.585 -28.0993) 
(list 4480.5625 -27.9493)))
(apply 'command (append '("pline") coords '("c")))
(setq currobj (ssadd (entlast) currobj))
(setq coords (list 
(list 4480.5625 -27.8063) 
(list 4554.585 -27.9563) 
(list 4554.585 -27.7793) 
(list 4480.5625 -27.7293)))
(apply 'command (append '("pline") coords '("c")))
(setq currobj (ssadd (entlast) currobj))
(setq coords (list 
(list 4480.5625 -27.5863) 
(list 4554.585 -27.6363) 
(list 4554.585 -27.4593) 
(list 4480.5625 -27.5093)))
(apply 'command (append '("pline") coords '("c")))
(setq currobj (ssadd (entlast) currobj))
(setq coords (list 
(list 4480.5625 -27.3663) 
(list 4554.585 -27.3163) 
(list 4554.585 -27.1393) 
(list 4480.5625 -27.2893)))
(apply 'command (append '("pline") coords '("c")))
(setq currobj (ssadd (entlast) currobj))
(setq coords (list 
(list 4480.5625 -27.1463) 
(list 4554.585 -26.9963) 
(list 4554.585 -26.8193) 
(list 4480.5625 -27.0693)))
(apply 'command (append '("pline") coords '("c")))
(setq currobj (ssadd (entlast) currobj))
(setq coords (list 
(list 4480.5625 -26.9263) 
(list 4554.585 -26.6763) 
(list 4554.585 -26.4993) 
(list 4480.5625 -26.8493)))
(apply 'command (append '("pline") coords '("c")))
(setq currobj (ssadd (entlast) currobj))
(setq coords (list 
(list 4480.5625 -26.7063) 
(list 4554.585 -26.3563) 
(list 4554.585 -26.1793) 
(list 4480.5625 -26.6293)))
(apply 'command (append '("pline") coords '("c")))
(setq currobj (ssadd (entlast) currobj))
(setq coords (list 
(list 4480.5625 -26.4863) 
(list 4554.585 -26.0363) 
(list 4554.585 -25.8593) 
(list 4480.5625 -26.4093)))
(apply 'command (append '("pline") coords '("c")))
(setq currobj (ssadd (entlast) currobj))
(setq coords (list 
(list 4480.5625 -26.2663) 
(list 4554.585 -25.7163) 
(list 4554.585 -25.5393) 
(list 4480.5625 -26.1893)))
(apply 'command (append '("pline") coords '("c")))
(setq currobj (ssadd (entlast) currobj))
(setq coords (list 
(list 4480.5625 -26.0463) 
(list 4554.585 -25.3963) 
(list 4554.585 -25.2193) 
(list 4480.5625 -25.9693)))
(apply 'command (append '("pline") coords '("c")))
(setq currobj (ssadd (entlast) currobj))
(setq coords (list 
(list 4479.4375 -25.9693) 
(list 4405.415 -25.2193) 
(list 4405.415 -25.3963) 
(list 4479.4375 -26.0463)))
(apply 'command (append '("pline") coords '("c")))
(setq currobj (ssadd (entlast) currobj))
(setq coords (list 
(list 4479.4375 -26.1893) 
(list 4405.415 -25.5393) 
(list 4405.415 -25.7163) 
(list 4479.4375 -26.2663)))
(apply 'command (append '("pline") coords '("c")))
(setq currobj (ssadd (entlast) currobj))
(setq coords (list 
(list 4479.4375 -26.4093) 
(list 4405.415 -25.8593) 
(list 4405.415 -26.0363) 
(list 4479.4375 -26.4863)))
(apply 'command (append '("pline") coords '("c")))
(setq currobj (ssadd (entlast) currobj))
(setq coords (list 
(list 4479.4375 -26.6293) 
(list 4405.415 -26.1793) 
(list 4405.415 -26.3563) 
(list 4479.4375 -26.7063)))
(apply 'command (append '("pline") coords '("c")))
(setq currobj (ssadd (entlast) currobj))
(setq coords (list 
(list 4479.4375 -26.8493) 
(list 4405.415 -26.4993) 
(list 4405.415 -26.6763) 
(list 4479.4375 -26.9263)))
(apply 'command (append '("pline") coords '("c")))
(setq currobj (ssadd (entlast) currobj))
(setq coords (list 
(list 4479.4375 -27.0693) 
(list 4405.415 -26.8193) 
(list 4405.415 -26.9963) 
(list 4479.4375 -27.1463)))
(apply 'command (append '("pline") coords '("c")))
(setq currobj (ssadd (entlast) currobj))
(setq coords (list 
(list 4479.4375 -27.2893) 
(list 4405.415 -27.1393) 
(list 4405.415 -27.3163) 
(list 4479.4375 -27.3663)))
(apply 'command (append '("pline") coords '("c")))
(setq currobj (ssadd (entlast) currobj))
(setq coords (list 
(list 4479.4375 -27.5093) 
(list 4405.415 -27.4593) 
(list 4405.415 -27.6363) 
(list 4479.4375 -27.5863)))
(apply 'command (append '("pline") coords '("c")))
(setq currobj (ssadd (entlast) currobj))
(setq coords (list 
(list 4479.4375 -27.7293) 
(list 4405.415 -27.7793) 
(list 4405.415 -27.9563) 
(list 4479.4375 -27.8063)))
(apply 'command (append '("pline") coords '("c")))
(setq currobj (ssadd (entlast) currobj))
(setq coords (list 
(list 4479.4375 -27.9493) 
(list 4405.415 -28.0993) 
(list 4405.415 -28.2763) 
(list 4479.4375 -28.0263)))
(apply 'command (append '("pline") coords '("c")))
(setq currobj (ssadd (entlast) currobj))
(setq coords (list 
(list 4479.4375 -28.1693) 
(list 4405.415 -28.4193) 
(list 4405.415 -28.5963) 
(list 4479.4375 -28.2463)))
(apply 'command (append '("pline") coords '("c")))
(setq currobj (ssadd (entlast) currobj))
(setq coords (list 
(list 4479.4375 -28.3893) 
(list 4405.415 -28.7393) 
(list 4405.415 -28.9163) 
(list 4479.4375 -28.4663)))
(apply 'command (append '("pline") coords '("c")))
(setq currobj (ssadd (entlast) currobj))
(setq coords (list 
(list 4479.4375 -28.6093) 
(list 4405.415 -29.0593) 
(list 4405.415 -29.2363) 
(list 4479.4375 -28.6863)))
(apply 'command (append '("pline") coords '("c")))
(setq currobj (ssadd (entlast) currobj))
(setq coords (list 
(list 4479.4375 -28.8293) 
(list 4405.415 -29.3793) 
(list 4405.415 -29.5563) 
(list 4479.4375 -28.9063)))
(apply 'command (append '("pline") coords '("c")))
(setq currobj (ssadd (entlast) currobj))
(setq coords (list 
(list 4479.4375 -29.0493) 
(list 4405.415 -29.6993) 
(list 4405.415 -29.8763) 
(list 4479.4375 -29.1263)))
(apply 'command (append '("pline") coords '("c")))
(setq currobj (ssadd (entlast) currobj))
(command "_layer" "set" "nitride" "")
(command "_layer" "set" "text" "")
(command "_circle" "4479.0625,-40.2693" "0.075")
(command "_circle" "4479.0625,-39.9693" "0.075")
(command "_circle" "4479.0625,-39.6693" "0.075")
(command "_circle" "4479.0625,-39.3693" "0.075")
(command "_circle" "4479.0625,-39.0693" "0.075")
(command "_circle" "4478.7625,-40.2693" "0.075")
(command "_circle" "4478.7625,-39.9693" "0.075")
(command "_circle" "4478.7625,-39.6693" "0.075")
(command "_circle" "4478.7625,-39.3693" "0.075")
(command "_circle" "4478.7625,-39.0693" "0.075")
(command "_circle" "4478.4625,-40.2693" "0.075")
(command "_circle" "4478.4625,-39.9693" "0.075")
(command "_circle" "4478.4625,-39.6693" "0.075")
(command "_circle" "4478.4625,-39.3693" "0.075")
(command "_circle" "4478.4625,-39.0693" "0.075")
(command "_circle" "4478.1625,-40.2693" "0.075")
(command "_circle" "4478.1625,-39.9693" "0.075")
(command "_circle" "4478.1625,-39.6693" "0.075")
(command "_circle" "4478.1625,-39.3693" "0.075")
(command "_circle" "4478.1625,-39.0693" "0.075")
(command "_circle" "4477.8625,-40.2693" "0.075")
(command "_circle" "4477.8625,-39.9693" "0.075")
(command "_circle" "4477.8625,-39.6693" "0.075")
(command "_circle" "4477.8625,-39.3693" "0.075")
(command "_circle" "4477.8625,-39.0693" "0.075")
(command "_layer" "set" "nitride" "")
(setq coords (list 
(list 4480.2625 -14.8263) 
(list 4480.2625 100.8184) 
(list 4479.7375 100.8184) 
(list 4479.7375 -14.8263)))
(apply 'command (append '("pline") coords '("c")))
(setq currobj (ssadd (entlast) currobj))
(command "_layer" "set" "prebias" "")
(command "_rectangle" "4479.7375,-14.8263" "4480.2625,100.8184")
(setq currobj (ssadd (entlast) currobj))
(command "_layer" "set" "nitride" "")
(setq coords (list 
(list 4480.2625 100.8184) 
(list 4480.5625 110.8184) 
(list 4480.5625 110.8184) 
(list 4480.5625 111.8184) 
(list 4554.585 111.0684) 
(list 4554.585 116.0114) 
(list 4480.5625 115.2614) 
(list 4480.5625 116.2614) 
(list 4480.5625 116.2614) 
(list 4480.2625 126.2614) 
(list 4479.7375 126.2614) 
(list 4479.4375 116.2614) 
(list 4479.4375 116.2614) 
(list 4479.4375 115.2614) 
(list 4405.415 116.0114) 
(list 4405.415 111.0684) 
(list 4479.4375 111.8184) 
(list 4479.4375 110.8184) 
(list 4479.4375 110.8184) 
(list 4479.7375 100.8184)))
(apply 'command (append '("pline") coords '("c")))
(setq currobj (ssadd (entlast) currobj))
(command "_layer" "set" "prebias" "")
(setq coords (list 
(list 4479.4375 100.8184) 
(list 4479.4375 111.8184) 
(list 4405.415 111.0684) 
(list 4405.415 116.0114) 
(list 4479.4375 115.2614) 
(list 4479.4375 126.2614) 
(list 4480.5625 126.2614) 
(list 4480.5625 115.2614) 
(list 4554.585 116.0114) 
(list 4554.585 111.0684) 
(list 4480.5625 111.8184) 
(list 4480.5625 100.8184)))
(apply 'command (append '("pline") coords '("c")))
(setq currobj (ssadd (entlast) currobj))
(command "_layer" "set" "nitride" "")
(command "_layer" "set" "fda1" "")
(setq coords (list 
(list 4480.5625 111.9614) 
(list 4554.585 111.2114) 
(list 4554.585 111.3884) 
(list 4480.5625 112.0384)))
(apply 'command (append '("pline") coords '("c")))
(setq currobj (ssadd (entlast) currobj))
(setq coords (list 
(list 4480.5625 112.1814) 
(list 4554.585 111.5314) 
(list 4554.585 111.7084) 
(list 4480.5625 112.2584)))
(apply 'command (append '("pline") coords '("c")))
(setq currobj (ssadd (entlast) currobj))
(setq coords (list 
(list 4480.5625 112.4014) 
(list 4554.585 111.8514) 
(list 4554.585 112.0284) 
(list 4480.5625 112.4784)))
(apply 'command (append '("pline") coords '("c")))
(setq currobj (ssadd (entlast) currobj))
(setq coords (list 
(list 4480.5625 112.6214) 
(list 4554.585 112.1714) 
(list 4554.585 112.3484) 
(list 4480.5625 112.6984)))
(apply 'command (append '("pline") coords '("c")))
(setq currobj (ssadd (entlast) currobj))
(setq coords (list 
(list 4480.5625 112.8414) 
(list 4554.585 112.4914) 
(list 4554.585 112.6684) 
(list 4480.5625 112.9184)))
(apply 'command (append '("pline") coords '("c")))
(setq currobj (ssadd (entlast) currobj))
(setq coords (list 
(list 4480.5625 113.0614) 
(list 4554.585 112.8114) 
(list 4554.585 112.9884) 
(list 4480.5625 113.1384)))
(apply 'command (append '("pline") coords '("c")))
(setq currobj (ssadd (entlast) currobj))
(setq coords (list 
(list 4480.5625 113.2814) 
(list 4554.585 113.1314) 
(list 4554.585 113.3084) 
(list 4480.5625 113.3584)))
(apply 'command (append '("pline") coords '("c")))
(setq currobj (ssadd (entlast) currobj))
(setq coords (list 
(list 4480.5625 113.5014) 
(list 4554.585 113.4514) 
(list 4554.585 113.6284) 
(list 4480.5625 113.5784)))
(apply 'command (append '("pline") coords '("c")))
(setq currobj (ssadd (entlast) currobj))
(setq coords (list 
(list 4480.5625 113.7214) 
(list 4554.585 113.7714) 
(list 4554.585 113.9484) 
(list 4480.5625 113.7984)))
(apply 'command (append '("pline") coords '("c")))
(setq currobj (ssadd (entlast) currobj))
(setq coords (list 
(list 4480.5625 113.9414) 
(list 4554.585 114.0914) 
(list 4554.585 114.2684) 
(list 4480.5625 114.0184)))
(apply 'command (append '("pline") coords '("c")))
(setq currobj (ssadd (entlast) currobj))
(setq coords (list 
(list 4480.5625 114.1614) 
(list 4554.585 114.4114) 
(list 4554.585 114.5884) 
(list 4480.5625 114.2384)))
(apply 'command (append '("pline") coords '("c")))
(setq currobj (ssadd (entlast) currobj))
(setq coords (list 
(list 4480.5625 114.3814) 
(list 4554.585 114.7314) 
(list 4554.585 114.9084) 
(list 4480.5625 114.4584)))
(apply 'command (append '("pline") coords '("c")))
(setq currobj (ssadd (entlast) currobj))
(setq coords (list 
(list 4480.5625 114.6014) 
(list 4554.585 115.0514) 
(list 4554.585 115.2284) 
(list 4480.5625 114.6784)))
(apply 'command (append '("pline") coords '("c")))
(setq currobj (ssadd (entlast) currobj))
(setq coords (list 
(list 4480.5625 114.8214) 
(list 4554.585 115.3714) 
(list 4554.585 115.5484) 
(list 4480.5625 114.8984)))
(apply 'command (append '("pline") coords '("c")))
(setq currobj (ssadd (entlast) currobj))
(setq coords (list 
(list 4480.5625 115.0414) 
(list 4554.585 115.6914) 
(list 4554.585 115.8684) 
(list 4480.5625 115.1184)))
(apply 'command (append '("pline") coords '("c")))
(setq currobj (ssadd (entlast) currobj))
(setq coords (list 
(list 4479.4375 115.1184) 
(list 4405.415 115.8684) 
(list 4405.415 115.6914) 
(list 4479.4375 115.0414)))
(apply 'command (append '("pline") coords '("c")))
(setq currobj (ssadd (entlast) currobj))
(setq coords (list 
(list 4479.4375 114.8984) 
(list 4405.415 115.5484) 
(list 4405.415 115.3714) 
(list 4479.4375 114.8214)))
(apply 'command (append '("pline") coords '("c")))
(setq currobj (ssadd (entlast) currobj))
(setq coords (list 
(list 4479.4375 114.6784) 
(list 4405.415 115.2284) 
(list 4405.415 115.0514) 
(list 4479.4375 114.6014)))
(apply 'command (append '("pline") coords '("c")))
(setq currobj (ssadd (entlast) currobj))
(setq coords (list 
(list 4479.4375 114.4584) 
(list 4405.415 114.9084) 
(list 4405.415 114.7314) 
(list 4479.4375 114.3814)))
(apply 'command (append '("pline") coords '("c")))
(setq currobj (ssadd (entlast) currobj))
(setq coords (list 
(list 4479.4375 114.2384) 
(list 4405.415 114.5884) 
(list 4405.415 114.4114) 
(list 4479.4375 114.1614)))
(apply 'command (append '("pline") coords '("c")))
(setq currobj (ssadd (entlast) currobj))
(setq coords (list 
(list 4479.4375 114.0184) 
(list 4405.415 114.2684) 
(list 4405.415 114.0914) 
(list 4479.4375 113.9414)))
(apply 'command (append '("pline") coords '("c")))
(setq currobj (ssadd (entlast) currobj))
(setq coords (list 
(list 4479.4375 113.7984) 
(list 4405.415 113.9484) 
(list 4405.415 113.7714) 
(list 4479.4375 113.7214)))
(apply 'command (append '("pline") coords '("c")))
(setq currobj (ssadd (entlast) currobj))
(setq coords (list 
(list 4479.4375 113.5784) 
(list 4405.415 113.6284) 
(list 4405.415 113.4514) 
(list 4479.4375 113.5014)))
(apply 'command (append '("pline") coords '("c")))
(setq currobj (ssadd (entlast) currobj))
(setq coords (list 
(list 4479.4375 113.3584) 
(list 4405.415 113.3084) 
(list 4405.415 113.1314) 
(list 4479.4375 113.2814)))
(apply 'command (append '("pline") coords '("c")))
(setq currobj (ssadd (entlast) currobj))
(setq coords (list 
(list 4479.4375 113.1384) 
(list 4405.415 112.9884) 
(list 4405.415 112.8114) 
(list 4479.4375 113.0614)))
(apply 'command (append '("pline") coords '("c")))
(setq currobj (ssadd (entlast) currobj))
(setq coords (list 
(list 4479.4375 112.9184) 
(list 4405.415 112.6684) 
(list 4405.415 112.4914) 
(list 4479.4375 112.8414)))
(apply 'command (append '("pline") coords '("c")))
(setq currobj (ssadd (entlast) currobj))
(setq coords (list 
(list 4479.4375 112.6984) 
(list 4405.415 112.3484) 
(list 4405.415 112.1714) 
(list 4479.4375 112.6214)))
(apply 'command (append '("pline") coords '("c")))
(setq currobj (ssadd (entlast) currobj))
(setq coords (list 
(list 4479.4375 112.4784) 
(list 4405.415 112.0284) 
(list 4405.415 111.8514) 
(list 4479.4375 112.4014)))
(apply 'command (append '("pline") coords '("c")))
(setq currobj (ssadd (entlast) currobj))
(setq coords (list 
(list 4479.4375 112.2584) 
(list 4405.415 111.7084) 
(list 4405.415 111.5314) 
(list 4479.4375 112.1814)))
(apply 'command (append '("pline") coords '("c")))
(setq currobj (ssadd (entlast) currobj))
(setq coords (list 
(list 4479.4375 112.0384) 
(list 4405.415 111.3884) 
(list 4405.415 111.2114) 
(list 4479.4375 111.9614)))
(apply 'command (append '("pline") coords '("c")))
(setq currobj (ssadd (entlast) currobj))
(command "_layer" "set" "nitride" "")
(command "_layer" "set" "text" "")
(command "_circle" "4479.0625,100.8184" "0.075")
(command "_circle" "4479.0625,101.1184" "0.075")
(command "_circle" "4479.0625,101.4184" "0.075")
(command "_circle" "4479.0625,101.7184" "0.075")
(command "_circle" "4479.0625,102.0184" "0.075")
(command "_circle" "4478.7625,100.8184" "0.075")
(command "_circle" "4478.7625,101.1184" "0.075")
(command "_circle" "4478.7625,101.4184" "0.075")
(command "_circle" "4478.7625,101.7184" "0.075")
(command "_circle" "4478.7625,102.0184" "0.075")
(command "_circle" "4478.4625,100.8184" "0.075")
(command "_circle" "4478.4625,101.1184" "0.075")
(command "_circle" "4478.4625,101.4184" "0.075")
(command "_circle" "4478.4625,101.7184" "0.075")
(command "_circle" "4478.4625,102.0184" "0.075")
(command "_circle" "4478.1625,100.8184" "0.075")
(command "_circle" "4478.1625,101.1184" "0.075")
(command "_circle" "4478.1625,101.4184" "0.075")
(command "_circle" "4478.1625,101.7184" "0.075")
(command "_circle" "4478.1625,102.0184" "0.075")
(command "_circle" "4477.8625,100.8184" "0.075")
(command "_circle" "4477.8625,101.1184" "0.075")
(command "_circle" "4477.8625,101.4184" "0.075")
(command "_circle" "4477.8625,101.7184" "0.075")
(command "_circle" "4477.8625,102.0184" "0.075")
(command "_layer" "set" "nitride" "")
(setq coords (list 
(list 4480.2625 126.2614) 
(list 4480.2625 241.9061) 
(list 4479.7375 241.9061) 
(list 4479.7375 126.2614)))
(apply 'command (append '("pline") coords '("c")))
(setq currobj (ssadd (entlast) currobj))
(command "_layer" "set" "prebias" "")
(command "_rectangle" "4479.7375,126.2614" "4480.2625,241.9061")
(setq currobj (ssadd (entlast) currobj))
(command "_layer" "set" "nitride" "")
(setq coords (list 
(list 4480.2625 241.9061) 
(list 4480.5625 251.9061) 
(list 4480.5625 251.9061) 
(list 4480.5625 252.9061) 
(list 4554.585 252.1561) 
(list 4554.585 257.0991) 
(list 4480.5625 256.3491) 
(list 4480.5625 257.3491) 
(list 4480.5625 257.3491) 
(list 4480.2625 267.3491) 
(list 4479.7375 267.3491) 
(list 4479.4375 257.3491) 
(list 4479.4375 257.3491) 
(list 4479.4375 256.3491) 
(list 4405.415 257.0991) 
(list 4405.415 252.1561) 
(list 4479.4375 252.9061) 
(list 4479.4375 251.9061) 
(list 4479.4375 251.9061) 
(list 4479.7375 241.9061)))
(apply 'command (append '("pline") coords '("c")))
(setq currobj (ssadd (entlast) currobj))
(command "_layer" "set" "prebias" "")
(setq coords (list 
(list 4479.4375 241.9061) 
(list 4479.4375 252.9061) 
(list 4405.415 252.1561) 
(list 4405.415 257.0991) 
(list 4479.4375 256.3491) 
(list 4479.4375 267.3491) 
(list 4480.5625 267.3491) 
(list 4480.5625 256.3491) 
(list 4554.585 257.0991) 
(list 4554.585 252.1561) 
(list 4480.5625 252.9061) 
(list 4480.5625 241.9061)))
(apply 'command (append '("pline") coords '("c")))
(setq currobj (ssadd (entlast) currobj))
(command "_layer" "set" "nitride" "")
(command "_layer" "set" "fda1" "")
(setq coords (list 
(list 4480.5625 253.0491) 
(list 4554.585 252.2991) 
(list 4554.585 252.4761) 
(list 4480.5625 253.1261)))
(apply 'command (append '("pline") coords '("c")))
(setq currobj (ssadd (entlast) currobj))
(setq coords (list 
(list 4480.5625 253.2691) 
(list 4554.585 252.6191) 
(list 4554.585 252.7961) 
(list 4480.5625 253.3461)))
(apply 'command (append '("pline") coords '("c")))
(setq currobj (ssadd (entlast) currobj))
(setq coords (list 
(list 4480.5625 253.4891) 
(list 4554.585 252.9391) 
(list 4554.585 253.1161) 
(list 4480.5625 253.5661)))
(apply 'command (append '("pline") coords '("c")))
(setq currobj (ssadd (entlast) currobj))
(setq coords (list 
(list 4480.5625 253.7091) 
(list 4554.585 253.2591) 
(list 4554.585 253.4361) 
(list 4480.5625 253.7861)))
(apply 'command (append '("pline") coords '("c")))
(setq currobj (ssadd (entlast) currobj))
(setq coords (list 
(list 4480.5625 253.9291) 
(list 4554.585 253.5791) 
(list 4554.585 253.7561) 
(list 4480.5625 254.0061)))
(apply 'command (append '("pline") coords '("c")))
(setq currobj (ssadd (entlast) currobj))
(setq coords (list 
(list 4480.5625 254.1491) 
(list 4554.585 253.8991) 
(list 4554.585 254.0761) 
(list 4480.5625 254.2261)))
(apply 'command (append '("pline") coords '("c")))
(setq currobj (ssadd (entlast) currobj))
(setq coords (list 
(list 4480.5625 254.3691) 
(list 4554.585 254.2191) 
(list 4554.585 254.3961) 
(list 4480.5625 254.4461)))
(apply 'command (append '("pline") coords '("c")))
(setq currobj (ssadd (entlast) currobj))
(setq coords (list 
(list 4480.5625 254.5891) 
(list 4554.585 254.5391) 
(list 4554.585 254.7161) 
(list 4480.5625 254.6661)))
(apply 'command (append '("pline") coords '("c")))
(setq currobj (ssadd (entlast) currobj))
(setq coords (list 
(list 4480.5625 254.8091) 
(list 4554.585 254.8591) 
(list 4554.585 255.0361) 
(list 4480.5625 254.8861)))
(apply 'command (append '("pline") coords '("c")))
(setq currobj (ssadd (entlast) currobj))
(setq coords (list 
(list 4480.5625 255.0291) 
(list 4554.585 255.1791) 
(list 4554.585 255.3561) 
(list 4480.5625 255.1061)))
(apply 'command (append '("pline") coords '("c")))
(setq currobj (ssadd (entlast) currobj))
(setq coords (list 
(list 4480.5625 255.2491) 
(list 4554.585 255.4991) 
(list 4554.585 255.6761) 
(list 4480.5625 255.3261)))
(apply 'command (append '("pline") coords '("c")))
(setq currobj (ssadd (entlast) currobj))
(setq coords (list 
(list 4480.5625 255.4691) 
(list 4554.585 255.8191) 
(list 4554.585 255.9961) 
(list 4480.5625 255.5461)))
(apply 'command (append '("pline") coords '("c")))
(setq currobj (ssadd (entlast) currobj))
(setq coords (list 
(list 4480.5625 255.6891) 
(list 4554.585 256.1391) 
(list 4554.585 256.3161) 
(list 4480.5625 255.7661)))
(apply 'command (append '("pline") coords '("c")))
(setq currobj (ssadd (entlast) currobj))
(setq coords (list 
(list 4480.5625 255.9091) 
(list 4554.585 256.4591) 
(list 4554.585 256.6361) 
(list 4480.5625 255.9861)))
(apply 'command (append '("pline") coords '("c")))
(setq currobj (ssadd (entlast) currobj))
(setq coords (list 
(list 4480.5625 256.1291) 
(list 4554.585 256.7791) 
(list 4554.585 256.9561) 
(list 4480.5625 256.2061)))
(apply 'command (append '("pline") coords '("c")))
(setq currobj (ssadd (entlast) currobj))
(setq coords (list 
(list 4479.4375 256.2061) 
(list 4405.415 256.9561) 
(list 4405.415 256.7791) 
(list 4479.4375 256.1291)))
(apply 'command (append '("pline") coords '("c")))
(setq currobj (ssadd (entlast) currobj))
(setq coords (list 
(list 4479.4375 255.9861) 
(list 4405.415 256.6361) 
(list 4405.415 256.4591) 
(list 4479.4375 255.9091)))
(apply 'command (append '("pline") coords '("c")))
(setq currobj (ssadd (entlast) currobj))
(setq coords (list 
(list 4479.4375 255.7661) 
(list 4405.415 256.3161) 
(list 4405.415 256.1391) 
(list 4479.4375 255.6891)))
(apply 'command (append '("pline") coords '("c")))
(setq currobj (ssadd (entlast) currobj))
(setq coords (list 
(list 4479.4375 255.5461) 
(list 4405.415 255.9961) 
(list 4405.415 255.8191) 
(list 4479.4375 255.4691)))
(apply 'command (append '("pline") coords '("c")))
(setq currobj (ssadd (entlast) currobj))
(setq coords (list 
(list 4479.4375 255.3261) 
(list 4405.415 255.6761) 
(list 4405.415 255.4991) 
(list 4479.4375 255.2491)))
(apply 'command (append '("pline") coords '("c")))
(setq currobj (ssadd (entlast) currobj))
(setq coords (list 
(list 4479.4375 255.1061) 
(list 4405.415 255.3561) 
(list 4405.415 255.1791) 
(list 4479.4375 255.0291)))
(apply 'command (append '("pline") coords '("c")))
(setq currobj (ssadd (entlast) currobj))
(setq coords (list 
(list 4479.4375 254.8861) 
(list 4405.415 255.0361) 
(list 4405.415 254.8591) 
(list 4479.4375 254.8091)))
(apply 'command (append '("pline") coords '("c")))
(setq currobj (ssadd (entlast) currobj))
(setq coords (list 
(list 4479.4375 254.6661) 
(list 4405.415 254.7161) 
(list 4405.415 254.5391) 
(list 4479.4375 254.5891)))
(apply 'command (append '("pline") coords '("c")))
(setq currobj (ssadd (entlast) currobj))
(setq coords (list 
(list 4479.4375 254.4461) 
(list 4405.415 254.3961) 
(list 4405.415 254.2191) 
(list 4479.4375 254.3691)))
(apply 'command (append '("pline") coords '("c")))
(setq currobj (ssadd (entlast) currobj))
(setq coords (list 
(list 4479.4375 254.2261) 
(list 4405.415 254.0761) 
(list 4405.415 253.8991) 
(list 4479.4375 254.1491)))
(apply 'command (append '("pline") coords '("c")))
(setq currobj (ssadd (entlast) currobj))
(setq coords (list 
(list 4479.4375 254.0061) 
(list 4405.415 253.7561) 
(list 4405.415 253.5791) 
(list 4479.4375 253.9291)))
(apply 'command (append '("pline") coords '("c")))
(setq currobj (ssadd (entlast) currobj))
(setq coords (list 
(list 4479.4375 253.7861) 
(list 4405.415 253.4361) 
(list 4405.415 253.2591) 
(list 4479.4375 253.7091)))
(apply 'command (append '("pline") coords '("c")))
(setq currobj (ssadd (entlast) currobj))
(setq coords (list 
(list 4479.4375 253.5661) 
(list 4405.415 253.1161) 
(list 4405.415 252.9391) 
(list 4479.4375 253.4891)))
(apply 'command (append '("pline") coords '("c")))
(setq currobj (ssadd (entlast) currobj))
(setq coords (list 
(list 4479.4375 253.3461) 
(list 4405.415 252.7961) 
(list 4405.415 252.6191) 
(list 4479.4375 253.2691)))
(apply 'command (append '("pline") coords '("c")))
(setq currobj (ssadd (entlast) currobj))
(setq coords (list 
(list 4479.4375 253.1261) 
(list 4405.415 252.4761) 
(list 4405.415 252.2991) 
(list 4479.4375 253.0491)))
(apply 'command (append '("pline") coords '("c")))
(setq currobj (ssadd (entlast) currobj))
(command "_layer" "set" "nitride" "")
(command "_layer" "set" "text" "")
(command "_circle" "4479.0625,241.9061" "0.075")
(command "_circle" "4479.0625,242.2061" "0.075")
(command "_circle" "4479.0625,242.5061" "0.075")
(command "_circle" "4479.0625,242.8061" "0.075")
(command "_circle" "4479.0625,243.1061" "0.075")
(command "_circle" "4478.7625,241.9061" "0.075")
(command "_circle" "4478.7625,242.2061" "0.075")
(command "_circle" "4478.7625,242.5061" "0.075")
(command "_circle" "4478.7625,242.8061" "0.075")
(command "_circle" "4478.7625,243.1061" "0.075")
(command "_circle" "4478.4625,241.9061" "0.075")
(command "_circle" "4478.4625,242.2061" "0.075")
(command "_circle" "4478.4625,242.5061" "0.075")
(command "_circle" "4478.4625,242.8061" "0.075")
(command "_circle" "4478.4625,243.1061" "0.075")
(command "_circle" "4478.1625,241.9061" "0.075")
(command "_circle" "4478.1625,242.2061" "0.075")
(command "_circle" "4478.1625,242.5061" "0.075")
(command "_circle" "4478.1625,242.8061" "0.075")
(command "_circle" "4478.1625,243.1061" "0.075")
(command "_circle" "4477.8625,241.9061" "0.075")
(command "_circle" "4477.8625,242.2061" "0.075")
(command "_circle" "4477.8625,242.5061" "0.075")
(command "_circle" "4477.8625,242.8061" "0.075")
(command "_circle" "4477.8625,243.1061" "0.075")
(command "_layer" "set" "nitride" "")
(setq coords (list 
(list 4480.2625 267.3491) 
(list 4480.2625 382.9939) 
(list 4479.7375 382.9939) 
(list 4479.7375 267.3491)))
(apply 'command (append '("pline") coords '("c")))
(setq currobj (ssadd (entlast) currobj))
(command "_layer" "set" "prebias" "")
(command "_rectangle" "4479.7375,267.3491" "4480.2625,382.9939")
(setq currobj (ssadd (entlast) currobj))
(command "_layer" "set" "nitride" "")
(setq coords (list 
(list 4480.2625 382.9939) 
(list 4480.5625 392.9939) 
(list 4480.5625 392.9939) 
(list 4480.5625 393.9939) 
(list 4554.585 393.2439) 
(list 4554.585 398.1869) 
(list 4480.5625 397.4369) 
(list 4480.5625 398.4369) 
(list 4480.5625 398.4369) 
(list 4480.2625 408.4369) 
(list 4479.7375 408.4369) 
(list 4479.4375 398.4369) 
(list 4479.4375 398.4369) 
(list 4479.4375 397.4369) 
(list 4405.415 398.1869) 
(list 4405.415 393.2439) 
(list 4479.4375 393.9939) 
(list 4479.4375 392.9939) 
(list 4479.4375 392.9939) 
(list 4479.7375 382.9939)))
(apply 'command (append '("pline") coords '("c")))
(setq currobj (ssadd (entlast) currobj))
(command "_layer" "set" "prebias" "")
(setq coords (list 
(list 4479.4375 382.9939) 
(list 4479.4375 393.9939) 
(list 4405.415 393.2439) 
(list 4405.415 398.1869) 
(list 4479.4375 397.4369) 
(list 4479.4375 408.4369) 
(list 4480.5625 408.4369) 
(list 4480.5625 397.4369) 
(list 4554.585 398.1869) 
(list 4554.585 393.2439) 
(list 4480.5625 393.9939) 
(list 4480.5625 382.9939)))
(apply 'command (append '("pline") coords '("c")))
(setq currobj (ssadd (entlast) currobj))
(command "_layer" "set" "nitride" "")
(command "_layer" "set" "fda1" "")
(setq coords (list 
(list 4480.5625 394.1369) 
(list 4554.585 393.3869) 
(list 4554.585 393.5639) 
(list 4480.5625 394.2139)))
(apply 'command (append '("pline") coords '("c")))
(setq currobj (ssadd (entlast) currobj))
(setq coords (list 
(list 4480.5625 394.3569) 
(list 4554.585 393.7069) 
(list 4554.585 393.8839) 
(list 4480.5625 394.4339)))
(apply 'command (append '("pline") coords '("c")))
(setq currobj (ssadd (entlast) currobj))
(setq coords (list 
(list 4480.5625 394.5769) 
(list 4554.585 394.0269) 
(list 4554.585 394.2039) 
(list 4480.5625 394.6539)))
(apply 'command (append '("pline") coords '("c")))
(setq currobj (ssadd (entlast) currobj))
(setq coords (list 
(list 4480.5625 394.7969) 
(list 4554.585 394.3469) 
(list 4554.585 394.5239) 
(list 4480.5625 394.8739)))
(apply 'command (append '("pline") coords '("c")))
(setq currobj (ssadd (entlast) currobj))
(setq coords (list 
(list 4480.5625 395.0169) 
(list 4554.585 394.6669) 
(list 4554.585 394.8439) 
(list 4480.5625 395.0939)))
(apply 'command (append '("pline") coords '("c")))
(setq currobj (ssadd (entlast) currobj))
(setq coords (list 
(list 4480.5625 395.2369) 
(list 4554.585 394.9869) 
(list 4554.585 395.1639) 
(list 4480.5625 395.3139)))
(apply 'command (append '("pline") coords '("c")))
(setq currobj (ssadd (entlast) currobj))
(setq coords (list 
(list 4480.5625 395.4569) 
(list 4554.585 395.3069) 
(list 4554.585 395.4839) 
(list 4480.5625 395.5339)))
(apply 'command (append '("pline") coords '("c")))
(setq currobj (ssadd (entlast) currobj))
(setq coords (list 
(list 4480.5625 395.6769) 
(list 4554.585 395.6269) 
(list 4554.585 395.8039) 
(list 4480.5625 395.7539)))
(apply 'command (append '("pline") coords '("c")))
(setq currobj (ssadd (entlast) currobj))
(setq coords (list 
(list 4480.5625 395.8969) 
(list 4554.585 395.9469) 
(list 4554.585 396.1239) 
(list 4480.5625 395.9739)))
(apply 'command (append '("pline") coords '("c")))
(setq currobj (ssadd (entlast) currobj))
(setq coords (list 
(list 4480.5625 396.1169) 
(list 4554.585 396.2669) 
(list 4554.585 396.4439) 
(list 4480.5625 396.1939)))
(apply 'command (append '("pline") coords '("c")))
(setq currobj (ssadd (entlast) currobj))
(setq coords (list 
(list 4480.5625 396.3369) 
(list 4554.585 396.5869) 
(list 4554.585 396.7639) 
(list 4480.5625 396.4139)))
(apply 'command (append '("pline") coords '("c")))
(setq currobj (ssadd (entlast) currobj))
(setq coords (list 
(list 4480.5625 396.5569) 
(list 4554.585 396.9069) 
(list 4554.585 397.0839) 
(list 4480.5625 396.6339)))
(apply 'command (append '("pline") coords '("c")))
(setq currobj (ssadd (entlast) currobj))
(setq coords (list 
(list 4480.5625 396.7769) 
(list 4554.585 397.2269) 
(list 4554.585 397.4039) 
(list 4480.5625 396.8539)))
(apply 'command (append '("pline") coords '("c")))
(setq currobj (ssadd (entlast) currobj))
(setq coords (list 
(list 4480.5625 396.9969) 
(list 4554.585 397.5469) 
(list 4554.585 397.7239) 
(list 4480.5625 397.0739)))
(apply 'command (append '("pline") coords '("c")))
(setq currobj (ssadd (entlast) currobj))
(setq coords (list 
(list 4480.5625 397.2169) 
(list 4554.585 397.8669) 
(list 4554.585 398.0439) 
(list 4480.5625 397.2939)))
(apply 'command (append '("pline") coords '("c")))
(setq currobj (ssadd (entlast) currobj))
(setq coords (list 
(list 4479.4375 397.2939) 
(list 4405.415 398.0439) 
(list 4405.415 397.8669) 
(list 4479.4375 397.2169)))
(apply 'command (append '("pline") coords '("c")))
(setq currobj (ssadd (entlast) currobj))
(setq coords (list 
(list 4479.4375 397.0739) 
(list 4405.415 397.7239) 
(list 4405.415 397.5469) 
(list 4479.4375 396.9969)))
(apply 'command (append '("pline") coords '("c")))
(setq currobj (ssadd (entlast) currobj))
(setq coords (list 
(list 4479.4375 396.8539) 
(list 4405.415 397.4039) 
(list 4405.415 397.2269) 
(list 4479.4375 396.7769)))
(apply 'command (append '("pline") coords '("c")))
(setq currobj (ssadd (entlast) currobj))
(setq coords (list 
(list 4479.4375 396.6339) 
(list 4405.415 397.0839) 
(list 4405.415 396.9069) 
(list 4479.4375 396.5569)))
(apply 'command (append '("pline") coords '("c")))
(setq currobj (ssadd (entlast) currobj))
(setq coords (list 
(list 4479.4375 396.4139) 
(list 4405.415 396.7639) 
(list 4405.415 396.5869) 
(list 4479.4375 396.3369)))
(apply 'command (append '("pline") coords '("c")))
(setq currobj (ssadd (entlast) currobj))
(setq coords (list 
(list 4479.4375 396.1939) 
(list 4405.415 396.4439) 
(list 4405.415 396.2669) 
(list 4479.4375 396.1169)))
(apply 'command (append '("pline") coords '("c")))
(setq currobj (ssadd (entlast) currobj))
(setq coords (list 
(list 4479.4375 395.9739) 
(list 4405.415 396.1239) 
(list 4405.415 395.9469) 
(list 4479.4375 395.8969)))
(apply 'command (append '("pline") coords '("c")))
(setq currobj (ssadd (entlast) currobj))
(setq coords (list 
(list 4479.4375 395.7539) 
(list 4405.415 395.8039) 
(list 4405.415 395.6269) 
(list 4479.4375 395.6769)))
(apply 'command (append '("pline") coords '("c")))
(setq currobj (ssadd (entlast) currobj))
(setq coords (list 
(list 4479.4375 395.5339) 
(list 4405.415 395.4839) 
(list 4405.415 395.3069) 
(list 4479.4375 395.4569)))
(apply 'command (append '("pline") coords '("c")))
(setq currobj (ssadd (entlast) currobj))
(setq coords (list 
(list 4479.4375 395.3139) 
(list 4405.415 395.1639) 
(list 4405.415 394.9869) 
(list 4479.4375 395.2369)))
(apply 'command (append '("pline") coords '("c")))
(setq currobj (ssadd (entlast) currobj))
(setq coords (list 
(list 4479.4375 395.0939) 
(list 4405.415 394.8439) 
(list 4405.415 394.6669) 
(list 4479.4375 395.0169)))
(apply 'command (append '("pline") coords '("c")))
(setq currobj (ssadd (entlast) currobj))
(setq coords (list 
(list 4479.4375 394.8739) 
(list 4405.415 394.5239) 
(list 4405.415 394.3469) 
(list 4479.4375 394.7969)))
(apply 'command (append '("pline") coords '("c")))
(setq currobj (ssadd (entlast) currobj))
(setq coords (list 
(list 4479.4375 394.6539) 
(list 4405.415 394.2039) 
(list 4405.415 394.0269) 
(list 4479.4375 394.5769)))
(apply 'command (append '("pline") coords '("c")))
(setq currobj (ssadd (entlast) currobj))
(setq coords (list 
(list 4479.4375 394.4339) 
(list 4405.415 393.8839) 
(list 4405.415 393.7069) 
(list 4479.4375 394.3569)))
(apply 'command (append '("pline") coords '("c")))
(setq currobj (ssadd (entlast) currobj))
(setq coords (list 
(list 4479.4375 394.2139) 
(list 4405.415 393.5639) 
(list 4405.415 393.3869) 
(list 4479.4375 394.1369)))
(apply 'command (append '("pline") coords '("c")))
(setq currobj (ssadd (entlast) currobj))
(command "_layer" "set" "nitride" "")
(command "_layer" "set" "text" "")
(command "_circle" "4479.0625,382.9939" "0.075")
(command "_circle" "4479.0625,383.2939" "0.075")
(command "_circle" "4479.0625,383.5939" "0.075")
(command "_circle" "4479.0625,383.8939" "0.075")
(command "_circle" "4479.0625,384.1939" "0.075")
(command "_circle" "4478.7625,382.9939" "0.075")
(command "_circle" "4478.7625,383.2939" "0.075")
(command "_circle" "4478.7625,383.5939" "0.075")
(command "_circle" "4478.7625,383.8939" "0.075")
(command "_circle" "4478.7625,384.1939" "0.075")
(command "_circle" "4478.4625,382.9939" "0.075")
(command "_circle" "4478.4625,383.2939" "0.075")
(command "_circle" "4478.4625,383.5939" "0.075")
(command "_circle" "4478.4625,383.8939" "0.075")
(command "_circle" "4478.4625,384.1939" "0.075")
(command "_circle" "4478.1625,382.9939" "0.075")
(command "_circle" "4478.1625,383.2939" "0.075")
(command "_circle" "4478.1625,383.5939" "0.075")
(command "_circle" "4478.1625,383.8939" "0.075")
(command "_circle" "4478.1625,384.1939" "0.075")
(command "_circle" "4477.8625,382.9939" "0.075")
(command "_circle" "4477.8625,383.2939" "0.075")
(command "_circle" "4477.8625,383.5939" "0.075")
(command "_circle" "4477.8625,383.8939" "0.075")
(command "_circle" "4477.8625,384.1939" "0.075")
(command "_layer" "set" "nitride" "")
(setq coords (list 
(list 4480.2625 408.4369) 
(list 4480.2625 524.0816) 
(list 4479.7375 524.0816) 
(list 4479.7375 408.4369)))
(apply 'command (append '("pline") coords '("c")))
(setq currobj (ssadd (entlast) currobj))
(command "_layer" "set" "prebias" "")
(command "_rectangle" "4479.7375,408.4369" "4480.2625,524.0816")
(setq currobj (ssadd (entlast) currobj))
(command "_layer" "set" "nitride" "")
(setq coords (list 
(list 4480.2625 524.0816) 
(list 4480.5625 534.0816) 
(list 4480.5625 534.0816) 
(list 4480.5625 535.0816) 
(list 4554.585 534.3316) 
(list 4554.585 539.2746) 
(list 4480.5625 538.5246) 
(list 4480.5625 539.5246) 
(list 4480.5625 539.5246) 
(list 4480.2625 549.5246) 
(list 4479.7375 549.5246) 
(list 4479.4375 539.5246) 
(list 4479.4375 539.5246) 
(list 4479.4375 538.5246) 
(list 4405.415 539.2746) 
(list 4405.415 534.3316) 
(list 4479.4375 535.0816) 
(list 4479.4375 534.0816) 
(list 4479.4375 534.0816) 
(list 4479.7375 524.0816)))
(apply 'command (append '("pline") coords '("c")))
(setq currobj (ssadd (entlast) currobj))
(command "_layer" "set" "prebias" "")
(setq coords (list 
(list 4479.4375 524.0816) 
(list 4479.4375 535.0816) 
(list 4405.415 534.3316) 
(list 4405.415 539.2746) 
(list 4479.4375 538.5246) 
(list 4479.4375 549.5246) 
(list 4480.5625 549.5246) 
(list 4480.5625 538.5246) 
(list 4554.585 539.2746) 
(list 4554.585 534.3316) 
(list 4480.5625 535.0816) 
(list 4480.5625 524.0816)))
(apply 'command (append '("pline") coords '("c")))
(setq currobj (ssadd (entlast) currobj))
(command "_layer" "set" "nitride" "")
(command "_layer" "set" "fda1" "")
(setq coords (list 
(list 4480.5625 535.2246) 
(list 4554.585 534.4746) 
(list 4554.585 534.6516) 
(list 4480.5625 535.3016)))
(apply 'command (append '("pline") coords '("c")))
(setq currobj (ssadd (entlast) currobj))
(setq coords (list 
(list 4480.5625 535.4446) 
(list 4554.585 534.7946) 
(list 4554.585 534.9716) 
(list 4480.5625 535.5216)))
(apply 'command (append '("pline") coords '("c")))
(setq currobj (ssadd (entlast) currobj))
(setq coords (list 
(list 4480.5625 535.6646) 
(list 4554.585 535.1146) 
(list 4554.585 535.2916) 
(list 4480.5625 535.7416)))
(apply 'command (append '("pline") coords '("c")))
(setq currobj (ssadd (entlast) currobj))
(setq coords (list 
(list 4480.5625 535.8846) 
(list 4554.585 535.4346) 
(list 4554.585 535.6116) 
(list 4480.5625 535.9616)))
(apply 'command (append '("pline") coords '("c")))
(setq currobj (ssadd (entlast) currobj))
(setq coords (list 
(list 4480.5625 536.1046) 
(list 4554.585 535.7546) 
(list 4554.585 535.9316) 
(list 4480.5625 536.1816)))
(apply 'command (append '("pline") coords '("c")))
(setq currobj (ssadd (entlast) currobj))
(setq coords (list 
(list 4480.5625 536.3246) 
(list 4554.585 536.0746) 
(list 4554.585 536.2516) 
(list 4480.5625 536.4016)))
(apply 'command (append '("pline") coords '("c")))
(setq currobj (ssadd (entlast) currobj))
(setq coords (list 
(list 4480.5625 536.5446) 
(list 4554.585 536.3946) 
(list 4554.585 536.5716) 
(list 4480.5625 536.6216)))
(apply 'command (append '("pline") coords '("c")))
(setq currobj (ssadd (entlast) currobj))
(setq coords (list 
(list 4480.5625 536.7646) 
(list 4554.585 536.7146) 
(list 4554.585 536.8916) 
(list 4480.5625 536.8416)))
(apply 'command (append '("pline") coords '("c")))
(setq currobj (ssadd (entlast) currobj))
(setq coords (list 
(list 4480.5625 536.9846) 
(list 4554.585 537.0346) 
(list 4554.585 537.2116) 
(list 4480.5625 537.0616)))
(apply 'command (append '("pline") coords '("c")))
(setq currobj (ssadd (entlast) currobj))
(setq coords (list 
(list 4480.5625 537.2046) 
(list 4554.585 537.3546) 
(list 4554.585 537.5316) 
(list 4480.5625 537.2816)))
(apply 'command (append '("pline") coords '("c")))
(setq currobj (ssadd (entlast) currobj))
(setq coords (list 
(list 4480.5625 537.4246) 
(list 4554.585 537.6746) 
(list 4554.585 537.8516) 
(list 4480.5625 537.5016)))
(apply 'command (append '("pline") coords '("c")))
(setq currobj (ssadd (entlast) currobj))
(setq coords (list 
(list 4480.5625 537.6446) 
(list 4554.585 537.9946) 
(list 4554.585 538.1716) 
(list 4480.5625 537.7216)))
(apply 'command (append '("pline") coords '("c")))
(setq currobj (ssadd (entlast) currobj))
(setq coords (list 
(list 4480.5625 537.8646) 
(list 4554.585 538.3146) 
(list 4554.585 538.4916) 
(list 4480.5625 537.9416)))
(apply 'command (append '("pline") coords '("c")))
(setq currobj (ssadd (entlast) currobj))
(setq coords (list 
(list 4480.5625 538.0846) 
(list 4554.585 538.6346) 
(list 4554.585 538.8116) 
(list 4480.5625 538.1616)))
(apply 'command (append '("pline") coords '("c")))
(setq currobj (ssadd (entlast) currobj))
(setq coords (list 
(list 4480.5625 538.3046) 
(list 4554.585 538.9546) 
(list 4554.585 539.1316) 
(list 4480.5625 538.3816)))
(apply 'command (append '("pline") coords '("c")))
(setq currobj (ssadd (entlast) currobj))
(setq coords (list 
(list 4479.4375 538.3816) 
(list 4405.415 539.1316) 
(list 4405.415 538.9546) 
(list 4479.4375 538.3046)))
(apply 'command (append '("pline") coords '("c")))
(setq currobj (ssadd (entlast) currobj))
(setq coords (list 
(list 4479.4375 538.1616) 
(list 4405.415 538.8116) 
(list 4405.415 538.6346) 
(list 4479.4375 538.0846)))
(apply 'command (append '("pline") coords '("c")))
(setq currobj (ssadd (entlast) currobj))
(setq coords (list 
(list 4479.4375 537.9416) 
(list 4405.415 538.4916) 
(list 4405.415 538.3146) 
(list 4479.4375 537.8646)))
(apply 'command (append '("pline") coords '("c")))
(setq currobj (ssadd (entlast) currobj))
(setq coords (list 
(list 4479.4375 537.7216) 
(list 4405.415 538.1716) 
(list 4405.415 537.9946) 
(list 4479.4375 537.6446)))
(apply 'command (append '("pline") coords '("c")))
(setq currobj (ssadd (entlast) currobj))
(setq coords (list 
(list 4479.4375 537.5016) 
(list 4405.415 537.8516) 
(list 4405.415 537.6746) 
(list 4479.4375 537.4246)))
(apply 'command (append '("pline") coords '("c")))
(setq currobj (ssadd (entlast) currobj))
(setq coords (list 
(list 4479.4375 537.2816) 
(list 4405.415 537.5316) 
(list 4405.415 537.3546) 
(list 4479.4375 537.2046)))
(apply 'command (append '("pline") coords '("c")))
(setq currobj (ssadd (entlast) currobj))
(setq coords (list 
(list 4479.4375 537.0616) 
(list 4405.415 537.2116) 
(list 4405.415 537.0346) 
(list 4479.4375 536.9846)))
(apply 'command (append '("pline") coords '("c")))
(setq currobj (ssadd (entlast) currobj))
(setq coords (list 
(list 4479.4375 536.8416) 
(list 4405.415 536.8916) 
(list 4405.415 536.7146) 
(list 4479.4375 536.7646)))
(apply 'command (append '("pline") coords '("c")))
(setq currobj (ssadd (entlast) currobj))
(setq coords (list 
(list 4479.4375 536.6216) 
(list 4405.415 536.5716) 
(list 4405.415 536.3946) 
(list 4479.4375 536.5446)))
(apply 'command (append '("pline") coords '("c")))
(setq currobj (ssadd (entlast) currobj))
(setq coords (list 
(list 4479.4375 536.4016) 
(list 4405.415 536.2516) 
(list 4405.415 536.0746) 
(list 4479.4375 536.3246)))
(apply 'command (append '("pline") coords '("c")))
(setq currobj (ssadd (entlast) currobj))
(setq coords (list 
(list 4479.4375 536.1816) 
(list 4405.415 535.9316) 
(list 4405.415 535.7546) 
(list 4479.4375 536.1046)))
(apply 'command (append '("pline") coords '("c")))
(setq currobj (ssadd (entlast) currobj))
(setq coords (list 
(list 4479.4375 535.9616) 
(list 4405.415 535.6116) 
(list 4405.415 535.4346) 
(list 4479.4375 535.8846)))
(apply 'command (append '("pline") coords '("c")))
(setq currobj (ssadd (entlast) currobj))
(setq coords (list 
(list 4479.4375 535.7416) 
(list 4405.415 535.2916) 
(list 4405.415 535.1146) 
(list 4479.4375 535.6646)))
(apply 'command (append '("pline") coords '("c")))
(setq currobj (ssadd (entlast) currobj))
(setq coords (list 
(list 4479.4375 535.5216) 
(list 4405.415 534.9716) 
(list 4405.415 534.7946) 
(list 4479.4375 535.4446)))
(apply 'command (append '("pline") coords '("c")))
(setq currobj (ssadd (entlast) currobj))
(setq coords (list 
(list 4479.4375 535.3016) 
(list 4405.415 534.6516) 
(list 4405.415 534.4746) 
(list 4479.4375 535.2246)))
(apply 'command (append '("pline") coords '("c")))
(setq currobj (ssadd (entlast) currobj))
(command "_layer" "set" "nitride" "")
(command "_layer" "set" "text" "")
(command "_circle" "4479.0625,524.0816" "0.075")
(command "_circle" "4479.0625,524.3816" "0.075")
(command "_circle" "4479.0625,524.6816" "0.075")
(command "_circle" "4479.0625,524.9816" "0.075")
(command "_circle" "4479.0625,525.2816" "0.075")
(command "_circle" "4478.7625,524.0816" "0.075")
(command "_circle" "4478.7625,524.3816" "0.075")
(command "_circle" "4478.7625,524.6816" "0.075")
(command "_circle" "4478.7625,524.9816" "0.075")
(command "_circle" "4478.7625,525.2816" "0.075")
(command "_circle" "4478.4625,524.0816" "0.075")
(command "_circle" "4478.4625,524.3816" "0.075")
(command "_circle" "4478.4625,524.6816" "0.075")
(command "_circle" "4478.4625,524.9816" "0.075")
(command "_circle" "4478.4625,525.2816" "0.075")
(command "_circle" "4478.1625,524.0816" "0.075")
(command "_circle" "4478.1625,524.3816" "0.075")
(command "_circle" "4478.1625,524.6816" "0.075")
(command "_circle" "4478.1625,524.9816" "0.075")
(command "_circle" "4478.1625,525.2816" "0.075")
(command "_circle" "4477.8625,524.0816" "0.075")
(command "_circle" "4477.8625,524.3816" "0.075")
(command "_circle" "4477.8625,524.6816" "0.075")
(command "_circle" "4477.8625,524.9816" "0.075")
(command "_circle" "4477.8625,525.2816" "0.075")
(command "_layer" "set" "nitride" "")
(setq coords (list 
(list 4480.2625 549.5246) 
(list 4480.2625 665.1693) 
(list 4479.7375 665.1693) 
(list 4479.7375 549.5246)))
(apply 'command (append '("pline") coords '("c")))
(setq currobj (ssadd (entlast) currobj))
(command "_layer" "set" "prebias" "")
(command "_rectangle" "4479.7375,549.5246" "4480.2625,665.1693")
(setq currobj (ssadd (entlast) currobj))
(command "_layer" "set" "nitride" "")
(setq coords (list 
(list 4480.2625 665.1693) 
(list 4480.5625 675.1693) 
(list 4480.5625 675.1693) 
(list 4480.5625 676.1693) 
(list 4554.585 675.4193) 
(list 4554.585 680.3623) 
(list 4480.5625 679.6123) 
(list 4480.5625 680.6123) 
(list 4480.5625 680.6123) 
(list 4480.2625 690.6123) 
(list 4479.7375 690.6123) 
(list 4479.4375 680.6123) 
(list 4479.4375 680.6123) 
(list 4479.4375 679.6123) 
(list 4405.415 680.3623) 
(list 4405.415 675.4193) 
(list 4479.4375 676.1693) 
(list 4479.4375 675.1693) 
(list 4479.4375 675.1693) 
(list 4479.7375 665.1693)))
(apply 'command (append '("pline") coords '("c")))
(setq currobj (ssadd (entlast) currobj))
(command "_layer" "set" "prebias" "")
(setq coords (list 
(list 4479.4375 665.1693) 
(list 4479.4375 676.1693) 
(list 4405.415 675.4193) 
(list 4405.415 680.3623) 
(list 4479.4375 679.6123) 
(list 4479.4375 690.6123) 
(list 4480.5625 690.6123) 
(list 4480.5625 679.6123) 
(list 4554.585 680.3623) 
(list 4554.585 675.4193) 
(list 4480.5625 676.1693) 
(list 4480.5625 665.1693)))
(apply 'command (append '("pline") coords '("c")))
(setq currobj (ssadd (entlast) currobj))
(command "_layer" "set" "nitride" "")
(command "_layer" "set" "fda1" "")
(setq coords (list 
(list 4480.5625 676.3123) 
(list 4554.585 675.5623) 
(list 4554.585 675.7393) 
(list 4480.5625 676.3893)))
(apply 'command (append '("pline") coords '("c")))
(setq currobj (ssadd (entlast) currobj))
(setq coords (list 
(list 4480.5625 676.5323) 
(list 4554.585 675.8823) 
(list 4554.585 676.0593) 
(list 4480.5625 676.6093)))
(apply 'command (append '("pline") coords '("c")))
(setq currobj (ssadd (entlast) currobj))
(setq coords (list 
(list 4480.5625 676.7523) 
(list 4554.585 676.2023) 
(list 4554.585 676.3793) 
(list 4480.5625 676.8293)))
(apply 'command (append '("pline") coords '("c")))
(setq currobj (ssadd (entlast) currobj))
(setq coords (list 
(list 4480.5625 676.9723) 
(list 4554.585 676.5223) 
(list 4554.585 676.6993) 
(list 4480.5625 677.0493)))
(apply 'command (append '("pline") coords '("c")))
(setq currobj (ssadd (entlast) currobj))
(setq coords (list 
(list 4480.5625 677.1923) 
(list 4554.585 676.8423) 
(list 4554.585 677.0193) 
(list 4480.5625 677.2693)))
(apply 'command (append '("pline") coords '("c")))
(setq currobj (ssadd (entlast) currobj))
(setq coords (list 
(list 4480.5625 677.4123) 
(list 4554.585 677.1623) 
(list 4554.585 677.3393) 
(list 4480.5625 677.4893)))
(apply 'command (append '("pline") coords '("c")))
(setq currobj (ssadd (entlast) currobj))
(setq coords (list 
(list 4480.5625 677.6323) 
(list 4554.585 677.4823) 
(list 4554.585 677.6593) 
(list 4480.5625 677.7093)))
(apply 'command (append '("pline") coords '("c")))
(setq currobj (ssadd (entlast) currobj))
(setq coords (list 
(list 4480.5625 677.8523) 
(list 4554.585 677.8023) 
(list 4554.585 677.9793) 
(list 4480.5625 677.9293)))
(apply 'command (append '("pline") coords '("c")))
(setq currobj (ssadd (entlast) currobj))
(setq coords (list 
(list 4480.5625 678.0723) 
(list 4554.585 678.1223) 
(list 4554.585 678.2993) 
(list 4480.5625 678.1493)))
(apply 'command (append '("pline") coords '("c")))
(setq currobj (ssadd (entlast) currobj))
(setq coords (list 
(list 4480.5625 678.2923) 
(list 4554.585 678.4423) 
(list 4554.585 678.6193) 
(list 4480.5625 678.3693)))
(apply 'command (append '("pline") coords '("c")))
(setq currobj (ssadd (entlast) currobj))
(setq coords (list 
(list 4480.5625 678.5123) 
(list 4554.585 678.7623) 
(list 4554.585 678.9393) 
(list 4480.5625 678.5893)))
(apply 'command (append '("pline") coords '("c")))
(setq currobj (ssadd (entlast) currobj))
(setq coords (list 
(list 4480.5625 678.7323) 
(list 4554.585 679.0823) 
(list 4554.585 679.2593) 
(list 4480.5625 678.8093)))
(apply 'command (append '("pline") coords '("c")))
(setq currobj (ssadd (entlast) currobj))
(setq coords (list 
(list 4480.5625 678.9523) 
(list 4554.585 679.4023) 
(list 4554.585 679.5793) 
(list 4480.5625 679.0293)))
(apply 'command (append '("pline") coords '("c")))
(setq currobj (ssadd (entlast) currobj))
(setq coords (list 
(list 4480.5625 679.1723) 
(list 4554.585 679.7223) 
(list 4554.585 679.8993) 
(list 4480.5625 679.2493)))
(apply 'command (append '("pline") coords '("c")))
(setq currobj (ssadd (entlast) currobj))
(setq coords (list 
(list 4480.5625 679.3923) 
(list 4554.585 680.0423) 
(list 4554.585 680.2193) 
(list 4480.5625 679.4693)))
(apply 'command (append '("pline") coords '("c")))
(setq currobj (ssadd (entlast) currobj))
(setq coords (list 
(list 4479.4375 679.4693) 
(list 4405.415 680.2193) 
(list 4405.415 680.0423) 
(list 4479.4375 679.3923)))
(apply 'command (append '("pline") coords '("c")))
(setq currobj (ssadd (entlast) currobj))
(setq coords (list 
(list 4479.4375 679.2493) 
(list 4405.415 679.8993) 
(list 4405.415 679.7223) 
(list 4479.4375 679.1723)))
(apply 'command (append '("pline") coords '("c")))
(setq currobj (ssadd (entlast) currobj))
(setq coords (list 
(list 4479.4375 679.0293) 
(list 4405.415 679.5793) 
(list 4405.415 679.4023) 
(list 4479.4375 678.9523)))
(apply 'command (append '("pline") coords '("c")))
(setq currobj (ssadd (entlast) currobj))
(setq coords (list 
(list 4479.4375 678.8093) 
(list 4405.415 679.2593) 
(list 4405.415 679.0823) 
(list 4479.4375 678.7323)))
(apply 'command (append '("pline") coords '("c")))
(setq currobj (ssadd (entlast) currobj))
(setq coords (list 
(list 4479.4375 678.5893) 
(list 4405.415 678.9393) 
(list 4405.415 678.7623) 
(list 4479.4375 678.5123)))
(apply 'command (append '("pline") coords '("c")))
(setq currobj (ssadd (entlast) currobj))
(setq coords (list 
(list 4479.4375 678.3693) 
(list 4405.415 678.6193) 
(list 4405.415 678.4423) 
(list 4479.4375 678.2923)))
(apply 'command (append '("pline") coords '("c")))
(setq currobj (ssadd (entlast) currobj))
(setq coords (list 
(list 4479.4375 678.1493) 
(list 4405.415 678.2993) 
(list 4405.415 678.1223) 
(list 4479.4375 678.0723)))
(apply 'command (append '("pline") coords '("c")))
(setq currobj (ssadd (entlast) currobj))
(setq coords (list 
(list 4479.4375 677.9293) 
(list 4405.415 677.9793) 
(list 4405.415 677.8023) 
(list 4479.4375 677.8523)))
(apply 'command (append '("pline") coords '("c")))
(setq currobj (ssadd (entlast) currobj))
(setq coords (list 
(list 4479.4375 677.7093) 
(list 4405.415 677.6593) 
(list 4405.415 677.4823) 
(list 4479.4375 677.6323)))
(apply 'command (append '("pline") coords '("c")))
(setq currobj (ssadd (entlast) currobj))
(setq coords (list 
(list 4479.4375 677.4893) 
(list 4405.415 677.3393) 
(list 4405.415 677.1623) 
(list 4479.4375 677.4123)))
(apply 'command (append '("pline") coords '("c")))
(setq currobj (ssadd (entlast) currobj))
(setq coords (list 
(list 4479.4375 677.2693) 
(list 4405.415 677.0193) 
(list 4405.415 676.8423) 
(list 4479.4375 677.1923)))
(apply 'command (append '("pline") coords '("c")))
(setq currobj (ssadd (entlast) currobj))
(setq coords (list 
(list 4479.4375 677.0493) 
(list 4405.415 676.6993) 
(list 4405.415 676.5223) 
(list 4479.4375 676.9723)))
(apply 'command (append '("pline") coords '("c")))
(setq currobj (ssadd (entlast) currobj))
(setq coords (list 
(list 4479.4375 676.8293) 
(list 4405.415 676.3793) 
(list 4405.415 676.2023) 
(list 4479.4375 676.7523)))
(apply 'command (append '("pline") coords '("c")))
(setq currobj (ssadd (entlast) currobj))
(setq coords (list 
(list 4479.4375 676.6093) 
(list 4405.415 676.0593) 
(list 4405.415 675.8823) 
(list 4479.4375 676.5323)))
(apply 'command (append '("pline") coords '("c")))
(setq currobj (ssadd (entlast) currobj))
(setq coords (list 
(list 4479.4375 676.3893) 
(list 4405.415 675.7393) 
(list 4405.415 675.5623) 
(list 4479.4375 676.3123)))
(apply 'command (append '("pline") coords '("c")))
(setq currobj (ssadd (entlast) currobj))
(command "_layer" "set" "nitride" "")
(command "_layer" "set" "text" "")
(command "_circle" "4479.0625,665.1693" "0.075")
(command "_circle" "4479.0625,665.4693" "0.075")
(command "_circle" "4479.0625,665.7693" "0.075")
(command "_circle" "4479.0625,666.0693" "0.075")
(command "_circle" "4479.0625,666.3693" "0.075")
(command "_circle" "4478.7625,665.1693" "0.075")
(command "_circle" "4478.7625,665.4693" "0.075")
(command "_circle" "4478.7625,665.7693" "0.075")
(command "_circle" "4478.7625,666.0693" "0.075")
(command "_circle" "4478.7625,666.3693" "0.075")
(command "_circle" "4478.4625,665.1693" "0.075")
(command "_circle" "4478.4625,665.4693" "0.075")
(command "_circle" "4478.4625,665.7693" "0.075")
(command "_circle" "4478.4625,666.0693" "0.075")
(command "_circle" "4478.4625,666.3693" "0.075")
(command "_circle" "4478.1625,665.1693" "0.075")
(command "_circle" "4478.1625,665.4693" "0.075")
(command "_circle" "4478.1625,665.7693" "0.075")
(command "_circle" "4478.1625,666.0693" "0.075")
(command "_circle" "4478.1625,666.3693" "0.075")
(command "_circle" "4477.8625,665.1693" "0.075")
(command "_circle" "4477.8625,665.4693" "0.075")
(command "_circle" "4477.8625,665.7693" "0.075")
(command "_circle" "4477.8625,666.0693" "0.075")
(command "_circle" "4477.8625,666.3693" "0.075")
(command "_layer" "set" "nitride" "")
(setq coords (list 
(list 4480.2625 690.6123) 
(list 4480.2625 806.257) 
(list 4479.7375 806.257) 
(list 4479.7375 690.6123)))
(apply 'command (append '("pline") coords '("c")))
(setq currobj (ssadd (entlast) currobj))
(command "_layer" "set" "prebias" "")
(command "_rectangle" "4479.7375,690.6123" "4480.2625,806.257")
(setq currobj (ssadd (entlast) currobj))
(command "_layer" "set" "nitride" "")
(setq coords (list 
(list 4480.2625 806.257) 
(list 4480.5625 816.257) 
(list 4480.5625 816.257) 
(list 4480.5625 817.257) 
(list 4554.585 816.507) 
(list 4554.585 821.45) 
(list 4480.5625 820.7) 
(list 4480.5625 821.7) 
(list 4480.5625 821.7) 
(list 4480.2625 831.7) 
(list 4479.7375 831.7) 
(list 4479.4375 821.7) 
(list 4479.4375 821.7) 
(list 4479.4375 820.7) 
(list 4405.415 821.45) 
(list 4405.415 816.507) 
(list 4479.4375 817.257) 
(list 4479.4375 816.257) 
(list 4479.4375 816.257) 
(list 4479.7375 806.257)))
(apply 'command (append '("pline") coords '("c")))
(setq currobj (ssadd (entlast) currobj))
(command "_layer" "set" "prebias" "")
(setq coords (list 
(list 4479.4375 806.257) 
(list 4479.4375 817.257) 
(list 4405.415 816.507) 
(list 4405.415 821.45) 
(list 4479.4375 820.7) 
(list 4479.4375 831.7) 
(list 4480.5625 831.7) 
(list 4480.5625 820.7) 
(list 4554.585 821.45) 
(list 4554.585 816.507) 
(list 4480.5625 817.257) 
(list 4480.5625 806.257)))
(apply 'command (append '("pline") coords '("c")))
(setq currobj (ssadd (entlast) currobj))
(command "_layer" "set" "nitride" "")
(command "_layer" "set" "fda1" "")
(setq coords (list 
(list 4480.5625 817.4) 
(list 4554.585 816.65) 
(list 4554.585 816.827) 
(list 4480.5625 817.477)))
(apply 'command (append '("pline") coords '("c")))
(setq currobj (ssadd (entlast) currobj))
(setq coords (list 
(list 4480.5625 817.62) 
(list 4554.585 816.97) 
(list 4554.585 817.147) 
(list 4480.5625 817.697)))
(apply 'command (append '("pline") coords '("c")))
(setq currobj (ssadd (entlast) currobj))
(setq coords (list 
(list 4480.5625 817.84) 
(list 4554.585 817.29) 
(list 4554.585 817.467) 
(list 4480.5625 817.917)))
(apply 'command (append '("pline") coords '("c")))
(setq currobj (ssadd (entlast) currobj))
(setq coords (list 
(list 4480.5625 818.06) 
(list 4554.585 817.61) 
(list 4554.585 817.787) 
(list 4480.5625 818.137)))
(apply 'command (append '("pline") coords '("c")))
(setq currobj (ssadd (entlast) currobj))
(setq coords (list 
(list 4480.5625 818.28) 
(list 4554.585 817.93) 
(list 4554.585 818.107) 
(list 4480.5625 818.357)))
(apply 'command (append '("pline") coords '("c")))
(setq currobj (ssadd (entlast) currobj))
(setq coords (list 
(list 4480.5625 818.5) 
(list 4554.585 818.25) 
(list 4554.585 818.427) 
(list 4480.5625 818.577)))
(apply 'command (append '("pline") coords '("c")))
(setq currobj (ssadd (entlast) currobj))
(setq coords (list 
(list 4480.5625 818.72) 
(list 4554.585 818.57) 
(list 4554.585 818.747) 
(list 4480.5625 818.797)))
(apply 'command (append '("pline") coords '("c")))
(setq currobj (ssadd (entlast) currobj))
(setq coords (list 
(list 4480.5625 818.94) 
(list 4554.585 818.89) 
(list 4554.585 819.067) 
(list 4480.5625 819.017)))
(apply 'command (append '("pline") coords '("c")))
(setq currobj (ssadd (entlast) currobj))
(setq coords (list 
(list 4480.5625 819.16) 
(list 4554.585 819.21) 
(list 4554.585 819.387) 
(list 4480.5625 819.237)))
(apply 'command (append '("pline") coords '("c")))
(setq currobj (ssadd (entlast) currobj))
(setq coords (list 
(list 4480.5625 819.38) 
(list 4554.585 819.53) 
(list 4554.585 819.707) 
(list 4480.5625 819.457)))
(apply 'command (append '("pline") coords '("c")))
(setq currobj (ssadd (entlast) currobj))
(setq coords (list 
(list 4480.5625 819.6) 
(list 4554.585 819.85) 
(list 4554.585 820.027) 
(list 4480.5625 819.677)))
(apply 'command (append '("pline") coords '("c")))
(setq currobj (ssadd (entlast) currobj))
(setq coords (list 
(list 4480.5625 819.82) 
(list 4554.585 820.17) 
(list 4554.585 820.347) 
(list 4480.5625 819.897)))
(apply 'command (append '("pline") coords '("c")))
(setq currobj (ssadd (entlast) currobj))
(setq coords (list 
(list 4480.5625 820.04) 
(list 4554.585 820.49) 
(list 4554.585 820.667) 
(list 4480.5625 820.117)))
(apply 'command (append '("pline") coords '("c")))
(setq currobj (ssadd (entlast) currobj))
(setq coords (list 
(list 4480.5625 820.26) 
(list 4554.585 820.81) 
(list 4554.585 820.987) 
(list 4480.5625 820.337)))
(apply 'command (append '("pline") coords '("c")))
(setq currobj (ssadd (entlast) currobj))
(setq coords (list 
(list 4480.5625 820.48) 
(list 4554.585 821.13) 
(list 4554.585 821.307) 
(list 4480.5625 820.557)))
(apply 'command (append '("pline") coords '("c")))
(setq currobj (ssadd (entlast) currobj))
(setq coords (list 
(list 4479.4375 820.557) 
(list 4405.415 821.307) 
(list 4405.415 821.13) 
(list 4479.4375 820.48)))
(apply 'command (append '("pline") coords '("c")))
(setq currobj (ssadd (entlast) currobj))
(setq coords (list 
(list 4479.4375 820.337) 
(list 4405.415 820.987) 
(list 4405.415 820.81) 
(list 4479.4375 820.26)))
(apply 'command (append '("pline") coords '("c")))
(setq currobj (ssadd (entlast) currobj))
(setq coords (list 
(list 4479.4375 820.117) 
(list 4405.415 820.667) 
(list 4405.415 820.49) 
(list 4479.4375 820.04)))
(apply 'command (append '("pline") coords '("c")))
(setq currobj (ssadd (entlast) currobj))
(setq coords (list 
(list 4479.4375 819.897) 
(list 4405.415 820.347) 
(list 4405.415 820.17) 
(list 4479.4375 819.82)))
(apply 'command (append '("pline") coords '("c")))
(setq currobj (ssadd (entlast) currobj))
(setq coords (list 
(list 4479.4375 819.677) 
(list 4405.415 820.027) 
(list 4405.415 819.85) 
(list 4479.4375 819.6)))
(apply 'command (append '("pline") coords '("c")))
(setq currobj (ssadd (entlast) currobj))
(setq coords (list 
(list 4479.4375 819.457) 
(list 4405.415 819.707) 
(list 4405.415 819.53) 
(list 4479.4375 819.38)))
(apply 'command (append '("pline") coords '("c")))
(setq currobj (ssadd (entlast) currobj))
(setq coords (list 
(list 4479.4375 819.237) 
(list 4405.415 819.387) 
(list 4405.415 819.21) 
(list 4479.4375 819.16)))
(apply 'command (append '("pline") coords '("c")))
(setq currobj (ssadd (entlast) currobj))
(setq coords (list 
(list 4479.4375 819.017) 
(list 4405.415 819.067) 
(list 4405.415 818.89) 
(list 4479.4375 818.94)))
(apply 'command (append '("pline") coords '("c")))
(setq currobj (ssadd (entlast) currobj))
(setq coords (list 
(list 4479.4375 818.797) 
(list 4405.415 818.747) 
(list 4405.415 818.57) 
(list 4479.4375 818.72)))
(apply 'command (append '("pline") coords '("c")))
(setq currobj (ssadd (entlast) currobj))
(setq coords (list 
(list 4479.4375 818.577) 
(list 4405.415 818.427) 
(list 4405.415 818.25) 
(list 4479.4375 818.5)))
(apply 'command (append '("pline") coords '("c")))
(setq currobj (ssadd (entlast) currobj))
(setq coords (list 
(list 4479.4375 818.357) 
(list 4405.415 818.107) 
(list 4405.415 817.93) 
(list 4479.4375 818.28)))
(apply 'command (append '("pline") coords '("c")))
(setq currobj (ssadd (entlast) currobj))
(setq coords (list 
(list 4479.4375 818.137) 
(list 4405.415 817.787) 
(list 4405.415 817.61) 
(list 4479.4375 818.06)))
(apply 'command (append '("pline") coords '("c")))
(setq currobj (ssadd (entlast) currobj))
(setq coords (list 
(list 4479.4375 817.917) 
(list 4405.415 817.467) 
(list 4405.415 817.29) 
(list 4479.4375 817.84)))
(apply 'command (append '("pline") coords '("c")))
(setq currobj (ssadd (entlast) currobj))
(setq coords (list 
(list 4479.4375 817.697) 
(list 4405.415 817.147) 
(list 4405.415 816.97) 
(list 4479.4375 817.62)))
(apply 'command (append '("pline") coords '("c")))
(setq currobj (ssadd (entlast) currobj))
(setq coords (list 
(list 4479.4375 817.477) 
(list 4405.415 816.827) 
(list 4405.415 816.65) 
(list 4479.4375 817.4)))
(apply 'command (append '("pline") coords '("c")))
(setq currobj (ssadd (entlast) currobj))
(command "_layer" "set" "nitride" "")
(command "_layer" "set" "text" "")
(command "_circle" "4479.0625,806.257" "0.075")
(command "_circle" "4479.0625,806.557" "0.075")
(command "_circle" "4479.0625,806.857" "0.075")
(command "_circle" "4479.0625,807.157" "0.075")
(command "_circle" "4479.0625,807.457" "0.075")
(command "_circle" "4478.7625,806.257" "0.075")
(command "_circle" "4478.7625,806.557" "0.075")
(command "_circle" "4478.7625,806.857" "0.075")
(command "_circle" "4478.7625,807.157" "0.075")
(command "_circle" "4478.7625,807.457" "0.075")
(command "_circle" "4478.4625,806.257" "0.075")
(command "_circle" "4478.4625,806.557" "0.075")
(command "_circle" "4478.4625,806.857" "0.075")
(command "_circle" "4478.4625,807.157" "0.075")
(command "_circle" "4478.4625,807.457" "0.075")
(command "_circle" "4478.1625,806.257" "0.075")
(command "_circle" "4478.1625,806.557" "0.075")
(command "_circle" "4478.1625,806.857" "0.075")
(command "_circle" "4478.1625,807.157" "0.075")
(command "_circle" "4478.1625,807.457" "0.075")
(command "_circle" "4477.8625,806.257" "0.075")
(command "_circle" "4477.8625,806.557" "0.075")
(command "_circle" "4477.8625,806.857" "0.075")
(command "_circle" "4477.8625,807.157" "0.075")
(command "_circle" "4477.8625,807.457" "0.075")
(command "_layer" "set" "nitride" "")
(setq coords (list 
(list 4480.2625 831.7) 
(list 4480.2625 836.7) 
(list 4479.7375 836.7) 
(list 4479.7375 831.7)))
(apply 'command (append '("pline") coords '("c")))
(setq currobj (ssadd (entlast) currobj))
(command "_layer" "set" "prebias" "")
(command "_rectangle" "4479.7375,831.7" "4480.2625,836.7")
(setq currobj (ssadd (entlast) currobj))
(command "_layer" "set" "nitride" "")
(setq cooledsinglenanobeam14 currobj)
(setq currobj nil)
(setq currobj (ssadd))
; DRAWING PHOTONIC CRYSTAL
(command "_layer" "set" "negYjunc" "")
(setq coords (list 
(list 4480.135 866.7) 
(list 4480 851.7) 
(list 4480 866.7)))
(apply 'command (append '("pline") coords '("c")))
(setq currobj (ssadd (entlast) currobj))
(setq coords (list 
(list 4480.2625 836.7) 
(list 4480.415 866.7) 
(list 4481.106 866.7) 
(list 4481.106 836.7)))
(apply 'command (append '("pline") coords '("c")))
(setq currobj (ssadd (entlast) currobj))
(setq coords (list 
(list 4479.865 866.7) 
(list 4480 851.7) 
(list 4480 866.7)))
(apply 'command (append '("pline") coords '("c")))
(setq currobj (ssadd (entlast) currobj))
(setq coords (list 
(list 4479.7375 836.7) 
(list 4479.585 866.7) 
(list 4478.894 866.7) 
(list 4478.894 836.7)))
(apply 'command (append '("pline") coords '("c")))
(setq currobj (ssadd (entlast) currobj))
(command "_layer" "set" "nitride" "")
(setq yjunction14 currobj)
(setq currobj nil)
(setq currobj (ssadd))
(setq tap14 nil)
(setq tap14 (ssadd))
(command "_layer" "set" "phc" "")
(setq coords (list 
(list 4480 866.7) 
(list 4480.135 866.7) 
(list 4480.135 866.7103) 
(list 4480.135 866.7206) 
(list 4480.135 866.7308) 
(list 4480.135 866.7411) 
(list 4480.135 866.7514) 
(list 4480.135 866.7617) 
(list 4480.135 866.7719) 
(list 4480.135 866.7822) 
(list 4480.135 866.7925) 
(list 4480.135 866.8028) 
(list 4480.135 866.8131) 
(list 4480.135 866.8233) 
(list 4480.135 866.8336) 
(list 4480.135 866.8439) 
(list 4480.135 866.8542) 
(list 4480.135 866.8644) 
(list 4480.135 866.8747) 
(list 4480.135 866.885) 
(list 4480.135 866.8953) 
(list 4480.135 866.9056) 
(list 4480.135 866.9158) 
(list 4480.135 866.9261) 
(list 4480.135 866.9364) 
(list 4480.135 866.9467) 
(list 4480.135 866.9569) 
(list 4480.135 866.9672) 
(list 4480.135 866.9775) 
(list 4480.135 866.9878) 
(list 4480.135 866.9981) 
(list 4480.135 867.0083) 
(list 4480.135 867.0186) 
(list 4480.135 867.0289) 
(list 4480.135 867.0392) 
(list 4480.135 867.0494) 
(list 4480.135 867.0597) 
(list 4480.135 867.07) 
(list 4480 867.07)))
(apply 'command (append '("pline") coords '("c")))
(setq tap14 (ssadd (entlast) tap14))
(command "_mirror" (entlast) "" "4480,900" "4480,901" "No")
(setq tap14 (ssadd (entlast) tap14))
(setq coords (list 
(list 4480.4242 866.7) 
(list 4480.415 866.7) 
(list 4480.4153 866.7103) 
(list 4480.4155 866.7206) 
(list 4480.4157 866.7308) 
(list 4480.4158 866.7411) 
(list 4480.4159 866.7514) 
(list 4480.4158 866.7617) 
(list 4480.4157 866.7719) 
(list 4480.4155 866.7822) 
(list 4480.4152 866.7925) 
(list 4480.4148 866.8028) 
(list 4480.4143 866.8131) 
(list 4480.4138 866.8233) 
(list 4480.4133 866.8336) 
(list 4480.4128 866.8439) 
(list 4480.4123 866.8542) 
(list 4480.4118 866.8644) 
(list 4480.4114 866.8747) 
(list 4480.4111 866.885) 
(list 4480.411 866.8953) 
(list 4480.411 866.9056) 
(list 4480.4112 866.9158) 
(list 4480.4115 866.9261) 
(list 4480.412 866.9364) 
(list 4480.4127 866.9467) 
(list 4480.4135 866.9569) 
(list 4480.4145 866.9672) 
(list 4480.4155 866.9775) 
(list 4480.4167 866.9878) 
(list 4480.4179 866.9981) 
(list 4480.4191 867.0083) 
(list 4480.4203 867.0186) 
(list 4480.4214 867.0289) 
(list 4480.4224 867.0392) 
(list 4480.4232 867.0494) 
(list 4480.4238 867.0597) 
(list 4480.4242 867.07) 
(list 4480.4242 867.07)))
(apply 'command (append '("pline") coords '("c")))
(setq tap14 (ssadd (entlast) tap14))
(command "_mirror" (entlast) "" "4480,900" "4480,901" "No")
(setq tap14 (ssadd (entlast) tap14))
(setq coords (list 
(list 4481.106 866.7) 
(list 4480.4242 866.7) 
(list 4480.4242 866.7103) 
(list 4480.4242 866.7206) 
(list 4480.4242 866.7308) 
(list 4480.4242 866.7411) 
(list 4480.4242 866.7514) 
(list 4480.4242 866.7617) 
(list 4480.4242 866.7719) 
(list 4480.4242 866.7822) 
(list 4480.4242 866.7925) 
(list 4480.4242 866.8028) 
(list 4480.4242 866.8131) 
(list 4480.4242 866.8233) 
(list 4480.4242 866.8336) 
(list 4480.4242 866.8439) 
(list 4480.4242 866.8542) 
(list 4480.4242 866.8644) 
(list 4480.4242 866.8747) 
(list 4480.4242 866.885) 
(list 4480.4242 866.8953) 
(list 4480.4242 866.9056) 
(list 4480.4242 866.9158) 
(list 4480.4242 866.9261) 
(list 4480.4242 866.9364) 
(list 4480.4242 866.9467) 
(list 4480.4242 866.9569) 
(list 4480.4242 866.9672) 
(list 4480.4242 866.9775) 
(list 4480.4242 866.9878) 
(list 4480.4242 866.9981) 
(list 4480.4242 867.0083) 
(list 4480.4242 867.0186) 
(list 4480.4242 867.0289) 
(list 4480.4242 867.0392) 
(list 4480.4242 867.0494) 
(list 4480.4242 867.0597) 
(list 4480.4242 867.07) 
(list 4481.106 867.07)))
(apply 'command (append '("pline") coords '("c")))
(setq tap14 (ssadd (entlast) tap14))
(command "_mirror" (entlast) "" "4480,900" "4480,901" "No")
(setq tap14 (ssadd (entlast) tap14))
(setq coords (list 
(list 4480 867.07) 
(list 4480.135 867.07) 
(list 4480.135 867.0803) 
(list 4480.135 867.0906) 
(list 4480.135 867.1008) 
(list 4480.135 867.1111) 
(list 4480.135 867.1214) 
(list 4480.135 867.1317) 
(list 4480.135 867.1419) 
(list 4480.135 867.1522) 
(list 4480.135 867.1625) 
(list 4480.135 867.1728) 
(list 4480.135 867.1831) 
(list 4480.135 867.1933) 
(list 4480.135 867.2036) 
(list 4480.135 867.2139) 
(list 4480.135 867.2242) 
(list 4480.135 867.2344) 
(list 4480.135 867.2447) 
(list 4480.135 867.255) 
(list 4480.135 867.2653) 
(list 4480.135 867.2756) 
(list 4480.135 867.2858) 
(list 4480.135 867.2961) 
(list 4480.135 867.3064) 
(list 4480.135 867.3167) 
(list 4480.135 867.3269) 
(list 4480.135 867.3372) 
(list 4480.135 867.3475) 
(list 4480.135 867.3578) 
(list 4480.135 867.3681) 
(list 4480.135 867.3783) 
(list 4480.135 867.3886) 
(list 4480.135 867.3989) 
(list 4480.135 867.4092) 
(list 4480.135 867.4194) 
(list 4480.135 867.4297) 
(list 4480.135 867.44) 
(list 4480 867.44)))
(apply 'command (append '("pline") coords '("c")))
(setq tap14 (ssadd (entlast) tap14))
(command "_mirror" (entlast) "" "4480,900" "4480,901" "No")
(setq tap14 (ssadd (entlast) tap14))
(setq coords (list 
(list 4480.4334 867.07) 
(list 4480.4242 867.07) 
(list 4480.4243 867.0803) 
(list 4480.4242 867.0906) 
(list 4480.4237 867.1008) 
(list 4480.423 867.1111) 
(list 4480.422 867.1214) 
(list 4480.4208 867.1317) 
(list 4480.4193 867.1419) 
(list 4480.4177 867.1522) 
(list 4480.4159 867.1625) 
(list 4480.4141 867.1728) 
(list 4480.4122 867.1831) 
(list 4480.4103 867.1933) 
(list 4480.4086 867.2036) 
(list 4480.407 867.2139) 
(list 4480.4057 867.2242) 
(list 4480.4046 867.2344) 
(list 4480.4038 867.2447) 
(list 4480.4034 867.255) 
(list 4480.4034 867.2653) 
(list 4480.4038 867.2756) 
(list 4480.4046 867.2858) 
(list 4480.4057 867.2961) 
(list 4480.4073 867.3064) 
(list 4480.4092 867.3167) 
(list 4480.4113 867.3269) 
(list 4480.4137 867.3372) 
(list 4480.4163 867.3475) 
(list 4480.4189 867.3578) 
(list 4480.4216 867.3681) 
(list 4480.4241 867.3783) 
(list 4480.4265 867.3886) 
(list 4480.4286 867.3989) 
(list 4480.4305 867.4092) 
(list 4480.4319 867.4194) 
(list 4480.4329 867.4297) 
(list 4480.4334 867.44) 
(list 4480.4334 867.44)))
(apply 'command (append '("pline") coords '("c")))
(setq tap14 (ssadd (entlast) tap14))
(command "_mirror" (entlast) "" "4480,900" "4480,901" "No")
(setq tap14 (ssadd (entlast) tap14))
(setq coords (list 
(list 4481.106 867.07) 
(list 4480.4334 867.07) 
(list 4480.4334 867.0803) 
(list 4480.4334 867.0906) 
(list 4480.4334 867.1008) 
(list 4480.4334 867.1111) 
(list 4480.4334 867.1214) 
(list 4480.4334 867.1317) 
(list 4480.4334 867.1419) 
(list 4480.4334 867.1522) 
(list 4480.4334 867.1625) 
(list 4480.4334 867.1728) 
(list 4480.4334 867.1831) 
(list 4480.4334 867.1933) 
(list 4480.4334 867.2036) 
(list 4480.4334 867.2139) 
(list 4480.4334 867.2242) 
(list 4480.4334 867.2344) 
(list 4480.4334 867.2447) 
(list 4480.4334 867.255) 
(list 4480.4334 867.2653) 
(list 4480.4334 867.2756) 
(list 4480.4334 867.2858) 
(list 4480.4334 867.2961) 
(list 4480.4334 867.3064) 
(list 4480.4334 867.3167) 
(list 4480.4334 867.3269) 
(list 4480.4334 867.3372) 
(list 4480.4334 867.3475) 
(list 4480.4334 867.3578) 
(list 4480.4334 867.3681) 
(list 4480.4334 867.3783) 
(list 4480.4334 867.3886) 
(list 4480.4334 867.3989) 
(list 4480.4334 867.4092) 
(list 4480.4334 867.4194) 
(list 4480.4334 867.4297) 
(list 4480.4334 867.44) 
(list 4481.106 867.44)))
(apply 'command (append '("pline") coords '("c")))
(setq tap14 (ssadd (entlast) tap14))
(command "_mirror" (entlast) "" "4480,900" "4480,901" "No")
(setq tap14 (ssadd (entlast) tap14))
(setq coords (list 
(list 4480 867.44) 
(list 4480.135 867.44) 
(list 4480.135 867.4503) 
(list 4480.135 867.4606) 
(list 4480.135 867.4708) 
(list 4480.135 867.4811) 
(list 4480.135 867.4914) 
(list 4480.135 867.5017) 
(list 4480.135 867.5119) 
(list 4480.135 867.5222) 
(list 4480.135 867.5325) 
(list 4480.135 867.5428) 
(list 4480.135 867.5531) 
(list 4480.135 867.5633) 
(list 4480.135 867.5736) 
(list 4480.135 867.5839) 
(list 4480.135 867.5942) 
(list 4480.135 867.6044) 
(list 4480.135 867.6147) 
(list 4480.135 867.625) 
(list 4480.135 867.6353) 
(list 4480.135 867.6456) 
(list 4480.135 867.6558) 
(list 4480.135 867.6661) 
(list 4480.135 867.6764) 
(list 4480.135 867.6867) 
(list 4480.135 867.6969) 
(list 4480.135 867.7072) 
(list 4480.135 867.7175) 
(list 4480.135 867.7278) 
(list 4480.135 867.7381) 
(list 4480.135 867.7483) 
(list 4480.135 867.7586) 
(list 4480.135 867.7689) 
(list 4480.135 867.7792) 
(list 4480.135 867.7894) 
(list 4480.135 867.7997) 
(list 4480.135 867.81) 
(list 4480 867.81)))
(apply 'command (append '("pline") coords '("c")))
(setq tap14 (ssadd (entlast) tap14))
(command "_mirror" (entlast) "" "4480,900" "4480,901" "No")
(setq tap14 (ssadd (entlast) tap14))
(setq coords (list 
(list 4480.4426 867.44) 
(list 4480.4334 867.44) 
(list 4480.4334 867.4503) 
(list 4480.4329 867.4606) 
(list 4480.4318 867.4708) 
(list 4480.4302 867.4811) 
(list 4480.4282 867.4914) 
(list 4480.4258 867.5017) 
(list 4480.423 867.5119) 
(list 4480.4199 867.5222) 
(list 4480.4167 867.5325) 
(list 4480.4133 867.5428) 
(list 4480.41 867.5531) 
(list 4480.4068 867.5633) 
(list 4480.4039 867.5736) 
(list 4480.4013 867.5839) 
(list 4480.3991 867.5942) 
(list 4480.3973 867.6044) 
(list 4480.3962 867.6147) 
(list 4480.3957 867.625) 
(list 4480.3958 867.6353) 
(list 4480.3965 867.6456) 
(list 4480.398 867.6558) 
(list 4480.4 867.6661) 
(list 4480.4026 867.6764) 
(list 4480.4057 867.6867) 
(list 4480.4092 867.6969) 
(list 4480.413 867.7072) 
(list 4480.417 867.7175) 
(list 4480.4211 867.7278) 
(list 4480.4252 867.7381) 
(list 4480.4291 867.7483) 
(list 4480.4327 867.7586) 
(list 4480.4359 867.7689) 
(list 4480.4385 867.7792) 
(list 4480.4406 867.7894) 
(list 4480.442 867.7997) 
(list 4480.4426 867.81) 
(list 4480.4426 867.81)))
(apply 'command (append '("pline") coords '("c")))
(setq tap14 (ssadd (entlast) tap14))
(command "_mirror" (entlast) "" "4480,900" "4480,901" "No")
(setq tap14 (ssadd (entlast) tap14))
(setq coords (list 
(list 4481.106 867.44) 
(list 4480.4426 867.44) 
(list 4480.4426 867.4503) 
(list 4480.4426 867.4606) 
(list 4480.4426 867.4708) 
(list 4480.4426 867.4811) 
(list 4480.4426 867.4914) 
(list 4480.4426 867.5017) 
(list 4480.4426 867.5119) 
(list 4480.4426 867.5222) 
(list 4480.4426 867.5325) 
(list 4480.4426 867.5428) 
(list 4480.4426 867.5531) 
(list 4480.4426 867.5633) 
(list 4480.4426 867.5736) 
(list 4480.4426 867.5839) 
(list 4480.4426 867.5942) 
(list 4480.4426 867.6044) 
(list 4480.4426 867.6147) 
(list 4480.4426 867.625) 
(list 4480.4426 867.6353) 
(list 4480.4426 867.6456) 
(list 4480.4426 867.6558) 
(list 4480.4426 867.6661) 
(list 4480.4426 867.6764) 
(list 4480.4426 867.6867) 
(list 4480.4426 867.6969) 
(list 4480.4426 867.7072) 
(list 4480.4426 867.7175) 
(list 4480.4426 867.7278) 
(list 4480.4426 867.7381) 
(list 4480.4426 867.7483) 
(list 4480.4426 867.7586) 
(list 4480.4426 867.7689) 
(list 4480.4426 867.7792) 
(list 4480.4426 867.7894) 
(list 4480.4426 867.7997) 
(list 4480.4426 867.81) 
(list 4481.106 867.81)))
(apply 'command (append '("pline") coords '("c")))
(setq tap14 (ssadd (entlast) tap14))
(command "_mirror" (entlast) "" "4480,900" "4480,901" "No")
(setq tap14 (ssadd (entlast) tap14))
(setq coords (list 
(list 4480 867.81) 
(list 4480.135 867.81) 
(list 4480.135 867.8203) 
(list 4480.135 867.8306) 
(list 4480.135 867.8408) 
(list 4480.135 867.8511) 
(list 4480.135 867.8614) 
(list 4480.135 867.8717) 
(list 4480.135 867.8819) 
(list 4480.135 867.8922) 
(list 4480.135 867.9025) 
(list 4480.135 867.9128) 
(list 4480.135 867.9231) 
(list 4480.135 867.9333) 
(list 4480.135 867.9436) 
(list 4480.135 867.9539) 
(list 4480.135 867.9642) 
(list 4480.135 867.9744) 
(list 4480.135 867.9847) 
(list 4480.135 867.995) 
(list 4480.135 868.0053) 
(list 4480.135 868.0156) 
(list 4480.135 868.0258) 
(list 4480.135 868.0361) 
(list 4480.135 868.0464) 
(list 4480.135 868.0567) 
(list 4480.135 868.0669) 
(list 4480.135 868.0772) 
(list 4480.135 868.0875) 
(list 4480.135 868.0978) 
(list 4480.135 868.1081) 
(list 4480.135 868.1183) 
(list 4480.135 868.1286) 
(list 4480.135 868.1389) 
(list 4480.135 868.1492) 
(list 4480.135 868.1594) 
(list 4480.135 868.1697) 
(list 4480.135 868.18) 
(list 4480 868.18)))
(apply 'command (append '("pline") coords '("c")))
(setq tap14 (ssadd (entlast) tap14))
(command "_mirror" (entlast) "" "4480,900" "4480,901" "No")
(setq tap14 (ssadd (entlast) tap14))
(setq coords (list 
(list 4480.4518 867.81) 
(list 4480.4426 867.81) 
(list 4480.4425 867.8203) 
(list 4480.4416 867.8306) 
(list 4480.4399 867.8408) 
(list 4480.4375 867.8511) 
(list 4480.4344 867.8614) 
(list 4480.4307 867.8717) 
(list 4480.4266 867.8819) 
(list 4480.4221 867.8922) 
(list 4480.4174 867.9025) 
(list 4480.4126 867.9128) 
(list 4480.4079 867.9231) 
(list 4480.4033 867.9333) 
(list 4480.3992 867.9436) 
(list 4480.3955 867.9539) 
(list 4480.3925 867.9642) 
(list 4480.3901 867.9744) 
(list 4480.3886 867.9847) 
(list 4480.3879 867.995) 
(list 4480.3882 868.0053) 
(list 4480.3893 868.0156) 
(list 4480.3914 868.0258) 
(list 4480.3942 868.0361) 
(list 4480.3979 868.0464) 
(list 4480.4022 868.0567) 
(list 4480.407 868.0669) 
(list 4480.4123 868.0772) 
(list 4480.4177 868.0875) 
(list 4480.4233 868.0978) 
(list 4480.4288 868.1081) 
(list 4480.434 868.1183) 
(list 4480.4388 868.1286) 
(list 4480.4431 868.1389) 
(list 4480.4466 868.1492) 
(list 4480.4493 868.1594) 
(list 4480.451 868.1697) 
(list 4480.4518 868.18) 
(list 4480.4518 868.18)))
(apply 'command (append '("pline") coords '("c")))
(setq tap14 (ssadd (entlast) tap14))
(command "_mirror" (entlast) "" "4480,900" "4480,901" "No")
(setq tap14 (ssadd (entlast) tap14))
(setq coords (list 
(list 4481.106 867.81) 
(list 4480.4518 867.81) 
(list 4480.4518 867.8203) 
(list 4480.4518 867.8306) 
(list 4480.4518 867.8408) 
(list 4480.4518 867.8511) 
(list 4480.4518 867.8614) 
(list 4480.4518 867.8717) 
(list 4480.4518 867.8819) 
(list 4480.4518 867.8922) 
(list 4480.4518 867.9025) 
(list 4480.4518 867.9128) 
(list 4480.4518 867.9231) 
(list 4480.4518 867.9333) 
(list 4480.4518 867.9436) 
(list 4480.4518 867.9539) 
(list 4480.4518 867.9642) 
(list 4480.4518 867.9744) 
(list 4480.4518 867.9847) 
(list 4480.4518 867.995) 
(list 4480.4518 868.0053) 
(list 4480.4518 868.0156) 
(list 4480.4518 868.0258) 
(list 4480.4518 868.0361) 
(list 4480.4518 868.0464) 
(list 4480.4518 868.0567) 
(list 4480.4518 868.0669) 
(list 4480.4518 868.0772) 
(list 4480.4518 868.0875) 
(list 4480.4518 868.0978) 
(list 4480.4518 868.1081) 
(list 4480.4518 868.1183) 
(list 4480.4518 868.1286) 
(list 4480.4518 868.1389) 
(list 4480.4518 868.1492) 
(list 4480.4518 868.1594) 
(list 4480.4518 868.1697) 
(list 4480.4518 868.18) 
(list 4481.106 868.18)))
(apply 'command (append '("pline") coords '("c")))
(setq tap14 (ssadd (entlast) tap14))
(command "_mirror" (entlast) "" "4480,900" "4480,901" "No")
(setq tap14 (ssadd (entlast) tap14))
(setq coords (list 
(list 4480 868.18) 
(list 4480.135 868.18) 
(list 4480.135 868.1903) 
(list 4480.135 868.2006) 
(list 4480.135 868.2108) 
(list 4480.135 868.2211) 
(list 4480.135 868.2314) 
(list 4480.135 868.2417) 
(list 4480.135 868.2519) 
(list 4480.135 868.2622) 
(list 4480.135 868.2725) 
(list 4480.135 868.2828) 
(list 4480.135 868.2931) 
(list 4480.135 868.3033) 
(list 4480.135 868.3136) 
(list 4480.135 868.3239) 
(list 4480.135 868.3342) 
(list 4480.135 868.3444) 
(list 4480.135 868.3547) 
(list 4480.135 868.365) 
(list 4480.135 868.3753) 
(list 4480.135 868.3856) 
(list 4480.135 868.3958) 
(list 4480.135 868.4061) 
(list 4480.135 868.4164) 
(list 4480.135 868.4267) 
(list 4480.135 868.4369) 
(list 4480.135 868.4472) 
(list 4480.135 868.4575) 
(list 4480.135 868.4678) 
(list 4480.135 868.4781) 
(list 4480.135 868.4883) 
(list 4480.135 868.4986) 
(list 4480.135 868.5089) 
(list 4480.135 868.5192) 
(list 4480.135 868.5294) 
(list 4480.135 868.5397) 
(list 4480.135 868.55) 
(list 4480 868.55)))
(apply 'command (append '("pline") coords '("c")))
(setq tap14 (ssadd (entlast) tap14))
(command "_mirror" (entlast) "" "4480,900" "4480,901" "No")
(setq tap14 (ssadd (entlast) tap14))
(setq coords (list 
(list 4480.461 868.18) 
(list 4480.4518 868.18) 
(list 4480.4515 868.1903) 
(list 4480.4502 868.2006) 
(list 4480.4479 868.2108) 
(list 4480.4447 868.2211) 
(list 4480.4406 868.2314) 
(list 4480.4357 868.2417) 
(list 4480.4302 868.2519) 
(list 4480.4243 868.2622) 
(list 4480.4181 868.2725) 
(list 4480.4118 868.2828) 
(list 4480.4057 868.2931) 
(list 4480.3998 868.3033) 
(list 4480.3945 868.3136) 
(list 4480.3898 868.3239) 
(list 4480.3859 868.3342) 
(list 4480.3829 868.3444) 
(list 4480.381 868.3547) 
(list 4480.3802 868.365) 
(list 4480.3806 868.3753) 
(list 4480.3821 868.3856) 
(list 4480.3848 868.3958) 
(list 4480.3885 868.4061) 
(list 4480.3932 868.4164) 
(list 4480.3987 868.4267) 
(list 4480.4048 868.4369) 
(list 4480.4115 868.4472) 
(list 4480.4185 868.4575) 
(list 4480.4255 868.4678) 
(list 4480.4324 868.4781) 
(list 4480.439 868.4883) 
(list 4480.445 868.4986) 
(list 4480.4503 868.5089) 
(list 4480.4547 868.5192) 
(list 4480.458 868.5294) 
(list 4480.4601 868.5397) 
(list 4480.461 868.55) 
(list 4480.461 868.55)))
(apply 'command (append '("pline") coords '("c")))
(setq tap14 (ssadd (entlast) tap14))
(command "_mirror" (entlast) "" "4480,900" "4480,901" "No")
(setq tap14 (ssadd (entlast) tap14))
(setq coords (list 
(list 4481.106 868.18) 
(list 4480.461 868.18) 
(list 4480.461 868.1903) 
(list 4480.461 868.2006) 
(list 4480.461 868.2108) 
(list 4480.461 868.2211) 
(list 4480.461 868.2314) 
(list 4480.461 868.2417) 
(list 4480.461 868.2519) 
(list 4480.461 868.2622) 
(list 4480.461 868.2725) 
(list 4480.461 868.2828) 
(list 4480.461 868.2931) 
(list 4480.461 868.3033) 
(list 4480.461 868.3136) 
(list 4480.461 868.3239) 
(list 4480.461 868.3342) 
(list 4480.461 868.3444) 
(list 4480.461 868.3547) 
(list 4480.461 868.365) 
(list 4480.461 868.3753) 
(list 4480.461 868.3856) 
(list 4480.461 868.3958) 
(list 4480.461 868.4061) 
(list 4480.461 868.4164) 
(list 4480.461 868.4267) 
(list 4480.461 868.4369) 
(list 4480.461 868.4472) 
(list 4480.461 868.4575) 
(list 4480.461 868.4678) 
(list 4480.461 868.4781) 
(list 4480.461 868.4883) 
(list 4480.461 868.4986) 
(list 4480.461 868.5089) 
(list 4480.461 868.5192) 
(list 4480.461 868.5294) 
(list 4480.461 868.5397) 
(list 4480.461 868.55) 
(list 4481.106 868.55)))
(apply 'command (append '("pline") coords '("c")))
(setq tap14 (ssadd (entlast) tap14))
(command "_mirror" (entlast) "" "4480,900" "4480,901" "No")
(setq tap14 (ssadd (entlast) tap14))
(setq coords (list 
(list 4480 868.55) 
(list 4480.135 868.55) 
(list 4480.135 868.5603) 
(list 4480.135 868.5706) 
(list 4480.135 868.5808) 
(list 4480.135 868.5911) 
(list 4480.135 868.6014) 
(list 4480.135 868.6117) 
(list 4480.135 868.6219) 
(list 4480.135 868.6322) 
(list 4480.135 868.6425) 
(list 4480.135 868.6528) 
(list 4480.135 868.6631) 
(list 4480.135 868.6733) 
(list 4480.135 868.6836) 
(list 4480.135 868.6939) 
(list 4480.135 868.7042) 
(list 4480.135 868.7144) 
(list 4480.135 868.7247) 
(list 4480.135 868.735) 
(list 4480.135 868.7453) 
(list 4480.135 868.7556) 
(list 4480.135 868.7658) 
(list 4480.135 868.7761) 
(list 4480.135 868.7864) 
(list 4480.135 868.7967) 
(list 4480.135 868.8069) 
(list 4480.135 868.8172) 
(list 4480.135 868.8275) 
(list 4480.135 868.8378) 
(list 4480.135 868.8481) 
(list 4480.135 868.8583) 
(list 4480.135 868.8686) 
(list 4480.135 868.8789) 
(list 4480.135 868.8892) 
(list 4480.135 868.8994) 
(list 4480.135 868.9097) 
(list 4480.135 868.92) 
(list 4480 868.92)))
(apply 'command (append '("pline") coords '("c")))
(setq tap14 (ssadd (entlast) tap14))
(command "_mirror" (entlast) "" "4480,900" "4480,901" "No")
(setq tap14 (ssadd (entlast) tap14))
(setq coords (list 
(list 4480.4702 868.55) 
(list 4480.461 868.55) 
(list 4480.4606 868.5603) 
(list 4480.4589 868.5706) 
(list 4480.456 868.5808) 
(list 4480.4519 868.5911) 
(list 4480.4467 868.6014) 
(list 4480.4407 868.6117) 
(list 4480.4339 868.6219) 
(list 4480.4265 868.6322) 
(list 4480.4189 868.6425) 
(list 4480.4111 868.6528) 
(list 4480.4035 868.6631) 
(list 4480.3963 868.6733) 
(list 4480.3898 868.6836) 
(list 4480.384 868.6939) 
(list 4480.3793 868.7042) 
(list 4480.3757 868.7144) 
(list 4480.3734 868.7247) 
(list 4480.3725 868.735) 
(list 4480.373 868.7453) 
(list 4480.3749 868.7556) 
(list 4480.3782 868.7658) 
(list 4480.3827 868.7761) 
(list 4480.3884 868.7864) 
(list 4480.3952 868.7967) 
(list 4480.4027 868.8069) 
(list 4480.4108 868.8172) 
(list 4480.4192 868.8275) 
(list 4480.4277 868.8378) 
(list 4480.4361 868.8481) 
(list 4480.444 868.8583) 
(list 4480.4512 868.8686) 
(list 4480.4575 868.8789) 
(list 4480.4627 868.8892) 
(list 4480.4667 868.8994) 
(list 4480.4692 868.9097) 
(list 4480.4702 868.92) 
(list 4480.4702 868.92)))
(apply 'command (append '("pline") coords '("c")))
(setq tap14 (ssadd (entlast) tap14))
(command "_mirror" (entlast) "" "4480,900" "4480,901" "No")
(setq tap14 (ssadd (entlast) tap14))
(setq coords (list 
(list 4481.106 868.55) 
(list 4480.4702 868.55) 
(list 4480.4702 868.5603) 
(list 4480.4702 868.5706) 
(list 4480.4702 868.5808) 
(list 4480.4702 868.5911) 
(list 4480.4702 868.6014) 
(list 4480.4702 868.6117) 
(list 4480.4702 868.6219) 
(list 4480.4702 868.6322) 
(list 4480.4702 868.6425) 
(list 4480.4702 868.6528) 
(list 4480.4702 868.6631) 
(list 4480.4702 868.6733) 
(list 4480.4702 868.6836) 
(list 4480.4702 868.6939) 
(list 4480.4702 868.7042) 
(list 4480.4702 868.7144) 
(list 4480.4702 868.7247) 
(list 4480.4702 868.735) 
(list 4480.4702 868.7453) 
(list 4480.4702 868.7556) 
(list 4480.4702 868.7658) 
(list 4480.4702 868.7761) 
(list 4480.4702 868.7864) 
(list 4480.4702 868.7967) 
(list 4480.4702 868.8069) 
(list 4480.4702 868.8172) 
(list 4480.4702 868.8275) 
(list 4480.4702 868.8378) 
(list 4480.4702 868.8481) 
(list 4480.4702 868.8583) 
(list 4480.4702 868.8686) 
(list 4480.4702 868.8789) 
(list 4480.4702 868.8892) 
(list 4480.4702 868.8994) 
(list 4480.4702 868.9097) 
(list 4480.4702 868.92) 
(list 4481.106 868.92)))
(apply 'command (append '("pline") coords '("c")))
(setq tap14 (ssadd (entlast) tap14))
(command "_mirror" (entlast) "" "4480,900" "4480,901" "No")
(setq tap14 (ssadd (entlast) tap14))
(setq coords (list 
(list 4480 868.92) 
(list 4480.135 868.92) 
(list 4480.135 868.9303) 
(list 4480.135 868.9406) 
(list 4480.135 868.9508) 
(list 4480.135 868.9611) 
(list 4480.135 868.9714) 
(list 4480.135 868.9817) 
(list 4480.135 868.9919) 
(list 4480.135 869.0022) 
(list 4480.135 869.0125) 
(list 4480.135 869.0228) 
(list 4480.135 869.0331) 
(list 4480.135 869.0433) 
(list 4480.135 869.0536) 
(list 4480.135 869.0639) 
(list 4480.135 869.0742) 
(list 4480.135 869.0844) 
(list 4480.135 869.0947) 
(list 4480.135 869.105) 
(list 4480.135 869.1153) 
(list 4480.135 869.1256) 
(list 4480.135 869.1358) 
(list 4480.135 869.1461) 
(list 4480.135 869.1564) 
(list 4480.135 869.1667) 
(list 4480.135 869.1769) 
(list 4480.135 869.1872) 
(list 4480.135 869.1975) 
(list 4480.135 869.2078) 
(list 4480.135 869.2181) 
(list 4480.135 869.2283) 
(list 4480.135 869.2386) 
(list 4480.135 869.2489) 
(list 4480.135 869.2592) 
(list 4480.135 869.2694) 
(list 4480.135 869.2797) 
(list 4480.135 869.29) 
(list 4480 869.29)))
(apply 'command (append '("pline") coords '("c")))
(setq tap14 (ssadd (entlast) tap14))
(command "_mirror" (entlast) "" "4480,900" "4480,901" "No")
(setq tap14 (ssadd (entlast) tap14))
(setq coords (list 
(list 4480.4794 868.92) 
(list 4480.4702 868.92) 
(list 4480.4697 868.9303) 
(list 4480.4676 868.9406) 
(list 4480.4641 868.9508) 
(list 4480.4591 868.9611) 
(list 4480.4529 868.9714) 
(list 4480.4456 868.9817) 
(list 4480.4375 868.9919) 
(list 4480.4287 869.0022) 
(list 4480.4196 869.0125) 
(list 4480.4104 869.0228) 
(list 4480.4014 869.0331) 
(list 4480.3928 869.0433) 
(list 4480.385 869.0536) 
(list 4480.3782 869.0639) 
(list 4480.3727 869.0742) 
(list 4480.3685 869.0844) 
(list 4480.3658 869.0947) 
(list 4480.3647 869.105) 
(list 4480.3654 869.1153) 
(list 4480.3677 869.1256) 
(list 4480.3716 869.1358) 
(list 4480.377 869.1461) 
(list 4480.3837 869.1564) 
(list 4480.3917 869.1667) 
(list 4480.4005 869.1769) 
(list 4480.41 869.1872) 
(list 4480.42 869.1975) 
(list 4480.4299 869.2078) 
(list 4480.4397 869.2181) 
(list 4480.4489 869.2283) 
(list 4480.4574 869.2386) 
(list 4480.4647 869.2489) 
(list 4480.4708 869.2592) 
(list 4480.4753 869.2694) 
(list 4480.4782 869.2797) 
(list 4480.4794 869.29) 
(list 4480.4794 869.29)))
(apply 'command (append '("pline") coords '("c")))
(setq tap14 (ssadd (entlast) tap14))
(command "_mirror" (entlast) "" "4480,900" "4480,901" "No")
(setq tap14 (ssadd (entlast) tap14))
(setq coords (list 
(list 4481.106 868.92) 
(list 4480.4794 868.92) 
(list 4480.4794 868.9303) 
(list 4480.4794 868.9406) 
(list 4480.4794 868.9508) 
(list 4480.4794 868.9611) 
(list 4480.4794 868.9714) 
(list 4480.4794 868.9817) 
(list 4480.4794 868.9919) 
(list 4480.4794 869.0022) 
(list 4480.4794 869.0125) 
(list 4480.4794 869.0228) 
(list 4480.4794 869.0331) 
(list 4480.4794 869.0433) 
(list 4480.4794 869.0536) 
(list 4480.4794 869.0639) 
(list 4480.4794 869.0742) 
(list 4480.4794 869.0844) 
(list 4480.4794 869.0947) 
(list 4480.4794 869.105) 
(list 4480.4794 869.1153) 
(list 4480.4794 869.1256) 
(list 4480.4794 869.1358) 
(list 4480.4794 869.1461) 
(list 4480.4794 869.1564) 
(list 4480.4794 869.1667) 
(list 4480.4794 869.1769) 
(list 4480.4794 869.1872) 
(list 4480.4794 869.1975) 
(list 4480.4794 869.2078) 
(list 4480.4794 869.2181) 
(list 4480.4794 869.2283) 
(list 4480.4794 869.2386) 
(list 4480.4794 869.2489) 
(list 4480.4794 869.2592) 
(list 4480.4794 869.2694) 
(list 4480.4794 869.2797) 
(list 4480.4794 869.29) 
(list 4481.106 869.29)))
(apply 'command (append '("pline") coords '("c")))
(setq tap14 (ssadd (entlast) tap14))
(command "_mirror" (entlast) "" "4480,900" "4480,901" "No")
(setq tap14 (ssadd (entlast) tap14))
(setq coords (list 
(list 4480 869.29) 
(list 4480.135 869.29) 
(list 4480.135 869.3003) 
(list 4480.135 869.3106) 
(list 4480.135 869.3208) 
(list 4480.135 869.3311) 
(list 4480.135 869.3414) 
(list 4480.135 869.3517) 
(list 4480.135 869.3619) 
(list 4480.135 869.3722) 
(list 4480.135 869.3825) 
(list 4480.135 869.3928) 
(list 4480.135 869.4031) 
(list 4480.135 869.4133) 
(list 4480.135 869.4236) 
(list 4480.135 869.4339) 
(list 4480.135 869.4442) 
(list 4480.135 869.4544) 
(list 4480.135 869.4647) 
(list 4480.135 869.475) 
(list 4480.135 869.4853) 
(list 4480.135 869.4956) 
(list 4480.135 869.5058) 
(list 4480.135 869.5161) 
(list 4480.135 869.5264) 
(list 4480.135 869.5367) 
(list 4480.135 869.5469) 
(list 4480.135 869.5572) 
(list 4480.135 869.5675) 
(list 4480.135 869.5778) 
(list 4480.135 869.5881) 
(list 4480.135 869.5983) 
(list 4480.135 869.6086) 
(list 4480.135 869.6189) 
(list 4480.135 869.6292) 
(list 4480.135 869.6394) 
(list 4480.135 869.6497) 
(list 4480.135 869.66) 
(list 4480 869.66)))
(apply 'command (append '("pline") coords '("c")))
(setq tap14 (ssadd (entlast) tap14))
(command "_mirror" (entlast) "" "4480,900" "4480,901" "No")
(setq tap14 (ssadd (entlast) tap14))
(setq coords (list 
(list 4480.4886 869.29) 
(list 4480.4794 869.29) 
(list 4480.4788 869.3003) 
(list 4480.4763 869.3106) 
(list 4480.4721 869.3208) 
(list 4480.4663 869.3311) 
(list 4480.4591 869.3414) 
(list 4480.4506 869.3517) 
(list 4480.4411 869.3619) 
(list 4480.4309 869.3722) 
(list 4480.4203 869.3825) 
(list 4480.4096 869.3928) 
(list 4480.3992 869.4031) 
(list 4480.3893 869.4133) 
(list 4480.3803 869.4236) 
(list 4480.3725 869.4339) 
(list 4480.3661 869.4442) 
(list 4480.3612 869.4544) 
(list 4480.3582 869.4647) 
(list 4480.357 869.475) 
(list 4480.3578 869.4853) 
(list 4480.3604 869.4956) 
(list 4480.365 869.5058) 
(list 4480.3712 869.5161) 
(list 4480.379 869.5264) 
(list 4480.3882 869.5367) 
(list 4480.3984 869.5469) 
(list 4480.4093 869.5572) 
(list 4480.4207 869.5675) 
(list 4480.4321 869.5778) 
(list 4480.4433 869.5881) 
(list 4480.4539 869.5983) 
(list 4480.4635 869.6086) 
(list 4480.472 869.6189) 
(list 4480.4789 869.6292) 
(list 4480.484 869.6394) 
(list 4480.4873 869.6497) 
(list 4480.4886 869.66) 
(list 4480.4886 869.66)))
(apply 'command (append '("pline") coords '("c")))
(setq tap14 (ssadd (entlast) tap14))
(command "_mirror" (entlast) "" "4480,900" "4480,901" "No")
(setq tap14 (ssadd (entlast) tap14))
(setq coords (list 
(list 4481.106 869.29) 
(list 4480.4886 869.29) 
(list 4480.4886 869.3003) 
(list 4480.4886 869.3106) 
(list 4480.4886 869.3208) 
(list 4480.4886 869.3311) 
(list 4480.4886 869.3414) 
(list 4480.4886 869.3517) 
(list 4480.4886 869.3619) 
(list 4480.4886 869.3722) 
(list 4480.4886 869.3825) 
(list 4480.4886 869.3928) 
(list 4480.4886 869.4031) 
(list 4480.4886 869.4133) 
(list 4480.4886 869.4236) 
(list 4480.4886 869.4339) 
(list 4480.4886 869.4442) 
(list 4480.4886 869.4544) 
(list 4480.4886 869.4647) 
(list 4480.4886 869.475) 
(list 4480.4886 869.4853) 
(list 4480.4886 869.4956) 
(list 4480.4886 869.5058) 
(list 4480.4886 869.5161) 
(list 4480.4886 869.5264) 
(list 4480.4886 869.5367) 
(list 4480.4886 869.5469) 
(list 4480.4886 869.5572) 
(list 4480.4886 869.5675) 
(list 4480.4886 869.5778) 
(list 4480.4886 869.5881) 
(list 4480.4886 869.5983) 
(list 4480.4886 869.6086) 
(list 4480.4886 869.6189) 
(list 4480.4886 869.6292) 
(list 4480.4886 869.6394) 
(list 4480.4886 869.6497) 
(list 4480.4886 869.66) 
(list 4481.106 869.66)))
(apply 'command (append '("pline") coords '("c")))
(setq tap14 (ssadd (entlast) tap14))
(command "_mirror" (entlast) "" "4480,900" "4480,901" "No")
(setq tap14 (ssadd (entlast) tap14))
(setq coords (list 
(list 4480 869.66) 
(list 4480.135 869.66) 
(list 4480.135 869.6703) 
(list 4480.135 869.6806) 
(list 4480.135 869.6908) 
(list 4480.135 869.7011) 
(list 4480.135 869.7114) 
(list 4480.135 869.7217) 
(list 4480.135 869.7319) 
(list 4480.135 869.7422) 
(list 4480.135 869.7525) 
(list 4480.135 869.7628) 
(list 4480.135 869.7731) 
(list 4480.135 869.7833) 
(list 4480.135 869.7936) 
(list 4480.135 869.8039) 
(list 4480.135 869.8142) 
(list 4480.135 869.8244) 
(list 4480.135 869.8347) 
(list 4480.135 869.845) 
(list 4480.135 869.8553) 
(list 4480.135 869.8656) 
(list 4480.135 869.8758) 
(list 4480.135 869.8861) 
(list 4480.135 869.8964) 
(list 4480.135 869.9067) 
(list 4480.135 869.9169) 
(list 4480.135 869.9272) 
(list 4480.135 869.9375) 
(list 4480.135 869.9478) 
(list 4480.135 869.9581) 
(list 4480.135 869.9683) 
(list 4480.135 869.9786) 
(list 4480.135 869.9889) 
(list 4480.135 869.9992) 
(list 4480.135 870.0094) 
(list 4480.135 870.0197) 
(list 4480.135 870.03) 
(list 4480 870.03)))
(apply 'command (append '("pline") coords '("c")))
(setq tap14 (ssadd (entlast) tap14))
(command "_mirror" (entlast) "" "4480,900" "4480,901" "No")
(setq tap14 (ssadd (entlast) tap14))
(setq coords (list 
(list 4480.4978 869.66) 
(list 4480.4886 869.66) 
(list 4480.4878 869.6703) 
(list 4480.485 869.6806) 
(list 4480.4802 869.6908) 
(list 4480.4736 869.7011) 
(list 4480.4653 869.7114) 
(list 4480.4556 869.7217) 
(list 4480.4447 869.7319) 
(list 4480.4331 869.7422) 
(list 4480.421 869.7525) 
(list 4480.4089 869.7628) 
(list 4480.397 869.7731) 
(list 4480.3858 869.7833) 
(list 4480.3756 869.7936) 
(list 4480.3667 869.8039) 
(list 4480.3595 869.8142) 
(list 4480.354 869.8244) 
(list 4480.3506 869.8347) 
(list 4480.3493 869.845) 
(list 4480.3501 869.8553) 
(list 4480.3532 869.8656) 
(list 4480.3584 869.8758) 
(list 4480.3655 869.8861) 
(list 4480.3743 869.8964) 
(list 4480.3847 869.9067) 
(list 4480.3962 869.9169) 
(list 4480.4086 869.9272) 
(list 4480.4214 869.9375) 
(list 4480.4343 869.9478) 
(list 4480.447 869.9581) 
(list 4480.4589 869.9683) 
(list 4480.4697 869.9786) 
(list 4480.4792 869.9889) 
(list 4480.4869 869.9992) 
(list 4480.4927 870.0094) 
(list 4480.4964 870.0197) 
(list 4480.4978 870.03) 
(list 4480.4978 870.03)))
(apply 'command (append '("pline") coords '("c")))
(setq tap14 (ssadd (entlast) tap14))
(command "_mirror" (entlast) "" "4480,900" "4480,901" "No")
(setq tap14 (ssadd (entlast) tap14))
(setq coords (list 
(list 4481.106 869.66) 
(list 4480.4978 869.66) 
(list 4480.4978 869.6703) 
(list 4480.4978 869.6806) 
(list 4480.4978 869.6908) 
(list 4480.4978 869.7011) 
(list 4480.4978 869.7114) 
(list 4480.4978 869.7217) 
(list 4480.4978 869.7319) 
(list 4480.4978 869.7422) 
(list 4480.4978 869.7525) 
(list 4480.4978 869.7628) 
(list 4480.4978 869.7731) 
(list 4480.4978 869.7833) 
(list 4480.4978 869.7936) 
(list 4480.4978 869.8039) 
(list 4480.4978 869.8142) 
(list 4480.4978 869.8244) 
(list 4480.4978 869.8347) 
(list 4480.4978 869.845) 
(list 4480.4978 869.8553) 
(list 4480.4978 869.8656) 
(list 4480.4978 869.8758) 
(list 4480.4978 869.8861) 
(list 4480.4978 869.8964) 
(list 4480.4978 869.9067) 
(list 4480.4978 869.9169) 
(list 4480.4978 869.9272) 
(list 4480.4978 869.9375) 
(list 4480.4978 869.9478) 
(list 4480.4978 869.9581) 
(list 4480.4978 869.9683) 
(list 4480.4978 869.9786) 
(list 4480.4978 869.9889) 
(list 4480.4978 869.9992) 
(list 4480.4978 870.0094) 
(list 4480.4978 870.0197) 
(list 4480.4978 870.03) 
(list 4481.106 870.03)))
(apply 'command (append '("pline") coords '("c")))
(setq tap14 (ssadd (entlast) tap14))
(command "_mirror" (entlast) "" "4480,900" "4480,901" "No")
(setq tap14 (ssadd (entlast) tap14))
(setq coords (list 
(list 4480 870.03) 
(list 4480.135 870.03) 
(list 4480.135 870.0403) 
(list 4480.135 870.0506) 
(list 4480.135 870.0608) 
(list 4480.135 870.0711) 
(list 4480.135 870.0814) 
(list 4480.135 870.0917) 
(list 4480.135 870.1019) 
(list 4480.135 870.1122) 
(list 4480.135 870.1225) 
(list 4480.135 870.1328) 
(list 4480.135 870.1431) 
(list 4480.135 870.1533) 
(list 4480.135 870.1636) 
(list 4480.135 870.1739) 
(list 4480.135 870.1842) 
(list 4480.135 870.1944) 
(list 4480.135 870.2047) 
(list 4480.135 870.215) 
(list 4480.135 870.2253) 
(list 4480.135 870.2356) 
(list 4480.135 870.2458) 
(list 4480.135 870.2561) 
(list 4480.135 870.2664) 
(list 4480.135 870.2767) 
(list 4480.135 870.2869) 
(list 4480.135 870.2972) 
(list 4480.135 870.3075) 
(list 4480.135 870.3178) 
(list 4480.135 870.3281) 
(list 4480.135 870.3383) 
(list 4480.135 870.3486) 
(list 4480.135 870.3589) 
(list 4480.135 870.3692) 
(list 4480.135 870.3794) 
(list 4480.135 870.3897) 
(list 4480.135 870.4) 
(list 4480 870.4)))
(apply 'command (append '("pline") coords '("c")))
(setq tap14 (ssadd (entlast) tap14))
(command "_mirror" (entlast) "" "4480,900" "4480,901" "No")
(setq tap14 (ssadd (entlast) tap14))
(setq coords (list 
(list 4480.507 870.03) 
(list 4480.4978 870.03) 
(list 4480.4969 870.0403) 
(list 4480.4937 870.0506) 
(list 4480.4883 870.0608) 
(list 4480.4808 870.0711) 
(list 4480.4714 870.0814) 
(list 4480.4605 870.0917) 
(list 4480.4484 870.1019) 
(list 4480.4353 870.1122) 
(list 4480.4218 870.1225) 
(list 4480.4082 870.1328) 
(list 4480.3949 870.1431) 
(list 4480.3823 870.1533) 
(list 4480.3709 870.1636) 
(list 4480.361 870.1739) 
(list 4480.3529 870.1842) 
(list 4480.3468 870.1944) 
(list 4480.343 870.2047) 
(list 4480.3415 870.215) 
(list 4480.3425 870.2253) 
(list 4480.346 870.2356) 
(list 4480.3518 870.2458) 
(list 4480.3597 870.2561) 
(list 4480.3696 870.2664) 
(list 4480.3812 870.2767) 
(list 4480.394 870.2869) 
(list 4480.4078 870.2972) 
(list 4480.4222 870.3075) 
(list 4480.4365 870.3178) 
(list 4480.4506 870.3281) 
(list 4480.4638 870.3383) 
(list 4480.4759 870.3486) 
(list 4480.4864 870.3589) 
(list 4480.495 870.3692) 
(list 4480.5014 870.3794) 
(list 4480.5055 870.3897) 
(list 4480.507 870.4) 
(list 4480.507 870.4)))
(apply 'command (append '("pline") coords '("c")))
(setq tap14 (ssadd (entlast) tap14))
(command "_mirror" (entlast) "" "4480,900" "4480,901" "No")
(setq tap14 (ssadd (entlast) tap14))
(setq coords (list 
(list 4481.106 870.03) 
(list 4480.507 870.03) 
(list 4480.507 870.0403) 
(list 4480.507 870.0506) 
(list 4480.507 870.0608) 
(list 4480.507 870.0711) 
(list 4480.507 870.0814) 
(list 4480.507 870.0917) 
(list 4480.507 870.1019) 
(list 4480.507 870.1122) 
(list 4480.507 870.1225) 
(list 4480.507 870.1328) 
(list 4480.507 870.1431) 
(list 4480.507 870.1533) 
(list 4480.507 870.1636) 
(list 4480.507 870.1739) 
(list 4480.507 870.1842) 
(list 4480.507 870.1944) 
(list 4480.507 870.2047) 
(list 4480.507 870.215) 
(list 4480.507 870.2253) 
(list 4480.507 870.2356) 
(list 4480.507 870.2458) 
(list 4480.507 870.2561) 
(list 4480.507 870.2664) 
(list 4480.507 870.2767) 
(list 4480.507 870.2869) 
(list 4480.507 870.2972) 
(list 4480.507 870.3075) 
(list 4480.507 870.3178) 
(list 4480.507 870.3281) 
(list 4480.507 870.3383) 
(list 4480.507 870.3486) 
(list 4480.507 870.3589) 
(list 4480.507 870.3692) 
(list 4480.507 870.3794) 
(list 4480.507 870.3897) 
(list 4480.507 870.4) 
(list 4481.106 870.4)))
(apply 'command (append '("pline") coords '("c")))
(setq tap14 (ssadd (entlast) tap14))
(command "_mirror" (entlast) "" "4480,900" "4480,901" "No")
(setq tap14 (ssadd (entlast) tap14))
(setq coords (list 
(list 4480 870.4) 
(list 4480.135 870.4) 
(list 4480.135 870.4103) 
(list 4480.135 870.4206) 
(list 4480.135 870.4308) 
(list 4480.135 870.4411) 
(list 4480.135 870.4514) 
(list 4480.135 870.4617) 
(list 4480.135 870.4719) 
(list 4480.135 870.4822) 
(list 4480.135 870.4925) 
(list 4480.135 870.5028) 
(list 4480.135 870.5131) 
(list 4480.135 870.5233) 
(list 4480.135 870.5336) 
(list 4480.135 870.5439) 
(list 4480.135 870.5542) 
(list 4480.135 870.5644) 
(list 4480.135 870.5747) 
(list 4480.135 870.585) 
(list 4480.135 870.5953) 
(list 4480.135 870.6056) 
(list 4480.135 870.6158) 
(list 4480.135 870.6261) 
(list 4480.135 870.6364) 
(list 4480.135 870.6467) 
(list 4480.135 870.6569) 
(list 4480.135 870.6672) 
(list 4480.135 870.6775) 
(list 4480.135 870.6878) 
(list 4480.135 870.6981) 
(list 4480.135 870.7083) 
(list 4480.135 870.7186) 
(list 4480.135 870.7289) 
(list 4480.135 870.7392) 
(list 4480.135 870.7494) 
(list 4480.135 870.7597) 
(list 4480.135 870.77) 
(list 4480 870.77)))
(apply 'command (append '("pline") coords '("c")))
(setq tap14 (ssadd (entlast) tap14))
(command "_mirror" (entlast) "" "4480,900" "4480,901" "No")
(setq tap14 (ssadd (entlast) tap14))
(setq coords (list 
(list 4480.5162 870.4) 
(list 4480.507 870.4) 
(list 4480.506 870.4103) 
(list 4480.5024 870.4206) 
(list 4480.4963 870.4308) 
(list 4480.488 870.4411) 
(list 4480.4776 870.4514) 
(list 4480.4655 870.4617) 
(list 4480.452 870.4719) 
(list 4480.4375 870.4822) 
(list 4480.4225 870.4925) 
(list 4480.4074 870.5028) 
(list 4480.3927 870.5131) 
(list 4480.3788 870.5233) 
(list 4480.3662 870.5336) 
(list 4480.3552 870.5439) 
(list 4480.3463 870.5542) 
(list 4480.3396 870.5644) 
(list 4480.3354 870.5747) 
(list 4480.3338 870.585) 
(list 4480.3349 870.5953) 
(list 4480.3388 870.6056) 
(list 4480.3452 870.6158) 
(list 4480.354 870.6261) 
(list 4480.3649 870.6364) 
(list 4480.3777 870.6467) 
(list 4480.3919 870.6569) 
(list 4480.4071 870.6672) 
(list 4480.4229 870.6775) 
(list 4480.4387 870.6878) 
(list 4480.4542 870.6981) 
(list 4480.4688 870.7083) 
(list 4480.4821 870.7186) 
(list 4480.4936 870.7289) 
(list 4480.5031 870.7392) 
(list 4480.5101 870.7494) 
(list 4480.5145 870.7597) 
(list 4480.5162 870.77) 
(list 4480.5162 870.77)))
(apply 'command (append '("pline") coords '("c")))
(setq tap14 (ssadd (entlast) tap14))
(command "_mirror" (entlast) "" "4480,900" "4480,901" "No")
(setq tap14 (ssadd (entlast) tap14))
(setq coords (list 
(list 4481.106 870.4) 
(list 4480.5162 870.4) 
(list 4480.5162 870.4103) 
(list 4480.5162 870.4206) 
(list 4480.5162 870.4308) 
(list 4480.5162 870.4411) 
(list 4480.5162 870.4514) 
(list 4480.5162 870.4617) 
(list 4480.5162 870.4719) 
(list 4480.5162 870.4822) 
(list 4480.5162 870.4925) 
(list 4480.5162 870.5028) 
(list 4480.5162 870.5131) 
(list 4480.5162 870.5233) 
(list 4480.5162 870.5336) 
(list 4480.5162 870.5439) 
(list 4480.5162 870.5542) 
(list 4480.5162 870.5644) 
(list 4480.5162 870.5747) 
(list 4480.5162 870.585) 
(list 4480.5162 870.5953) 
(list 4480.5162 870.6056) 
(list 4480.5162 870.6158) 
(list 4480.5162 870.6261) 
(list 4480.5162 870.6364) 
(list 4480.5162 870.6467) 
(list 4480.5162 870.6569) 
(list 4480.5162 870.6672) 
(list 4480.5162 870.6775) 
(list 4480.5162 870.6878) 
(list 4480.5162 870.6981) 
(list 4480.5162 870.7083) 
(list 4480.5162 870.7186) 
(list 4480.5162 870.7289) 
(list 4480.5162 870.7392) 
(list 4480.5162 870.7494) 
(list 4480.5162 870.7597) 
(list 4480.5162 870.77) 
(list 4481.106 870.77)))
(apply 'command (append '("pline") coords '("c")))
(setq tap14 (ssadd (entlast) tap14))
(command "_mirror" (entlast) "" "4480,900" "4480,901" "No")
(setq tap14 (ssadd (entlast) tap14))
(setq coords (list 
(list 4480 870.77) 
(list 4480.135 870.77) 
(list 4480.135 870.7803) 
(list 4480.135 870.7906) 
(list 4480.135 870.8008) 
(list 4480.135 870.8111) 
(list 4480.135 870.8214) 
(list 4480.135 870.8317) 
(list 4480.135 870.8419) 
(list 4480.135 870.8522) 
(list 4480.135 870.8625) 
(list 4480.135 870.8728) 
(list 4480.135 870.8831) 
(list 4480.135 870.8933) 
(list 4480.135 870.9036) 
(list 4480.135 870.9139) 
(list 4480.135 870.9242) 
(list 4480.135 870.9344) 
(list 4480.135 870.9447) 
(list 4480.135 870.955) 
(list 4480.135 870.9653) 
(list 4480.135 870.9756) 
(list 4480.135 870.9858) 
(list 4480.135 870.9961) 
(list 4480.135 871.0064) 
(list 4480.135 871.0167) 
(list 4480.135 871.0269) 
(list 4480.135 871.0372) 
(list 4480.135 871.0475) 
(list 4480.135 871.0578) 
(list 4480.135 871.0681) 
(list 4480.135 871.0783) 
(list 4480.135 871.0886) 
(list 4480.135 871.0989) 
(list 4480.135 871.1092) 
(list 4480.135 871.1194) 
(list 4480.135 871.1297) 
(list 4480.135 871.14) 
(list 4480 871.14)))
(apply 'command (append '("pline") coords '("c")))
(setq tap14 (ssadd (entlast) tap14))
(command "_mirror" (entlast) "" "4480,900" "4480,901" "No")
(setq tap14 (ssadd (entlast) tap14))
(setq coords (list 
(list 4480.5254 870.77) 
(list 4480.5162 870.77) 
(list 4480.515 870.7803) 
(list 4480.5111 870.7906) 
(list 4480.5044 870.8008) 
(list 4480.4952 870.8111) 
(list 4480.4838 870.8214) 
(list 4480.4705 870.8317) 
(list 4480.4556 870.8419) 
(list 4480.4397 870.8522) 
(list 4480.4232 870.8625) 
(list 4480.4067 870.8728) 
(list 4480.3906 870.8831) 
(list 4480.3753 870.8933) 
(list 4480.3615 870.9036) 
(list 4480.3495 870.9139) 
(list 4480.3397 870.9242) 
(list 4480.3323 870.9344) 
(list 4480.3278 870.9447) 
(list 4480.3261 870.955) 
(list 4480.3273 870.9653) 
(list 4480.3315 870.9756) 
(list 4480.3386 870.9858) 
(list 4480.3482 870.9961) 
(list 4480.3602 871.0064) 
(list 4480.3742 871.0167) 
(list 4480.3897 871.0269) 
(list 4480.4064 871.0372) 
(list 4480.4236 871.0475) 
(list 4480.441 871.0578) 
(list 4480.4578 871.0681) 
(list 4480.4738 871.0783) 
(list 4480.4883 871.0886) 
(list 4480.5008 871.0989) 
(list 4480.5111 871.1092) 
(list 4480.5188 871.1194) 
(list 4480.5236 871.1297) 
(list 4480.5254 871.14) 
(list 4480.5254 871.14)))
(apply 'command (append '("pline") coords '("c")))
(setq tap14 (ssadd (entlast) tap14))
(command "_mirror" (entlast) "" "4480,900" "4480,901" "No")
(setq tap14 (ssadd (entlast) tap14))
(setq coords (list 
(list 4481.106 870.77) 
(list 4480.5254 870.77) 
(list 4480.5254 870.7803) 
(list 4480.5254 870.7906) 
(list 4480.5254 870.8008) 
(list 4480.5254 870.8111) 
(list 4480.5254 870.8214) 
(list 4480.5254 870.8317) 
(list 4480.5254 870.8419) 
(list 4480.5254 870.8522) 
(list 4480.5254 870.8625) 
(list 4480.5254 870.8728) 
(list 4480.5254 870.8831) 
(list 4480.5254 870.8933) 
(list 4480.5254 870.9036) 
(list 4480.5254 870.9139) 
(list 4480.5254 870.9242) 
(list 4480.5254 870.9344) 
(list 4480.5254 870.9447) 
(list 4480.5254 870.955) 
(list 4480.5254 870.9653) 
(list 4480.5254 870.9756) 
(list 4480.5254 870.9858) 
(list 4480.5254 870.9961) 
(list 4480.5254 871.0064) 
(list 4480.5254 871.0167) 
(list 4480.5254 871.0269) 
(list 4480.5254 871.0372) 
(list 4480.5254 871.0475) 
(list 4480.5254 871.0578) 
(list 4480.5254 871.0681) 
(list 4480.5254 871.0783) 
(list 4480.5254 871.0886) 
(list 4480.5254 871.0989) 
(list 4480.5254 871.1092) 
(list 4480.5254 871.1194) 
(list 4480.5254 871.1297) 
(list 4480.5254 871.14) 
(list 4481.106 871.14)))
(apply 'command (append '("pline") coords '("c")))
(setq tap14 (ssadd (entlast) tap14))
(command "_mirror" (entlast) "" "4480,900" "4480,901" "No")
(setq tap14 (ssadd (entlast) tap14))
(setq coords (list 
(list 4480 871.14) 
(list 4480.135 871.14) 
(list 4480.135 871.1503) 
(list 4480.135 871.1606) 
(list 4480.135 871.1708) 
(list 4480.135 871.1811) 
(list 4480.135 871.1914) 
(list 4480.135 871.2017) 
(list 4480.135 871.2119) 
(list 4480.135 871.2222) 
(list 4480.135 871.2325) 
(list 4480.135 871.2428) 
(list 4480.135 871.2531) 
(list 4480.135 871.2633) 
(list 4480.135 871.2736) 
(list 4480.135 871.2839) 
(list 4480.135 871.2942) 
(list 4480.135 871.3044) 
(list 4480.135 871.3147) 
(list 4480.135 871.325) 
(list 4480.135 871.3353) 
(list 4480.135 871.3456) 
(list 4480.135 871.3558) 
(list 4480.135 871.3661) 
(list 4480.135 871.3764) 
(list 4480.135 871.3867) 
(list 4480.135 871.3969) 
(list 4480.135 871.4072) 
(list 4480.135 871.4175) 
(list 4480.135 871.4278) 
(list 4480.135 871.4381) 
(list 4480.135 871.4483) 
(list 4480.135 871.4586) 
(list 4480.135 871.4689) 
(list 4480.135 871.4792) 
(list 4480.135 871.4894) 
(list 4480.135 871.4997) 
(list 4480.135 871.51) 
(list 4480 871.51)))
(apply 'command (append '("pline") coords '("c")))
(setq tap14 (ssadd (entlast) tap14))
(command "_mirror" (entlast) "" "4480,900" "4480,901" "No")
(setq tap14 (ssadd (entlast) tap14))
(setq coords (list 
(list 4480.5346 871.14) 
(list 4480.5254 871.14) 
(list 4480.5241 871.1503) 
(list 4480.5198 871.1606) 
(list 4480.5125 871.1708) 
(list 4480.5024 871.1811) 
(list 4480.49 871.1914) 
(list 4480.4754 871.2017) 
(list 4480.4593 871.2119) 
(list 4480.4419 871.2222) 
(list 4480.424 871.2325) 
(list 4480.406 871.2428) 
(list 4480.3884 871.2531) 
(list 4480.3718 871.2633) 
(list 4480.3568 871.2736) 
(list 4480.3437 871.2839) 
(list 4480.3331 871.2942) 
(list 4480.3251 871.3044) 
(list 4480.3202 871.3147) 
(list 4480.3183 871.325) 
(list 4480.3197 871.3353) 
(list 4480.3243 871.3456) 
(list 4480.332 871.3558) 
(list 4480.3425 871.3661) 
(list 4480.3555 871.3764) 
(list 4480.3707 871.3867) 
(list 4480.3875 871.3969) 
(list 4480.4056 871.4072) 
(list 4480.4244 871.4175) 
(list 4480.4432 871.4278) 
(list 4480.4615 871.4381) 
(list 4480.4787 871.4483) 
(list 4480.4944 871.4586) 
(list 4480.508 871.4689) 
(list 4480.5192 871.4792) 
(list 4480.5275 871.4894) 
(list 4480.5327 871.4997) 
(list 4480.5346 871.51) 
(list 4480.5346 871.51)))
(apply 'command (append '("pline") coords '("c")))
(setq tap14 (ssadd (entlast) tap14))
(command "_mirror" (entlast) "" "4480,900" "4480,901" "No")
(setq tap14 (ssadd (entlast) tap14))
(setq coords (list 
(list 4481.106 871.14) 
(list 4480.5346 871.14) 
(list 4480.5346 871.1503) 
(list 4480.5346 871.1606) 
(list 4480.5346 871.1708) 
(list 4480.5346 871.1811) 
(list 4480.5346 871.1914) 
(list 4480.5346 871.2017) 
(list 4480.5346 871.2119) 
(list 4480.5346 871.2222) 
(list 4480.5346 871.2325) 
(list 4480.5346 871.2428) 
(list 4480.5346 871.2531) 
(list 4480.5346 871.2633) 
(list 4480.5346 871.2736) 
(list 4480.5346 871.2839) 
(list 4480.5346 871.2942) 
(list 4480.5346 871.3044) 
(list 4480.5346 871.3147) 
(list 4480.5346 871.325) 
(list 4480.5346 871.3353) 
(list 4480.5346 871.3456) 
(list 4480.5346 871.3558) 
(list 4480.5346 871.3661) 
(list 4480.5346 871.3764) 
(list 4480.5346 871.3867) 
(list 4480.5346 871.3969) 
(list 4480.5346 871.4072) 
(list 4480.5346 871.4175) 
(list 4480.5346 871.4278) 
(list 4480.5346 871.4381) 
(list 4480.5346 871.4483) 
(list 4480.5346 871.4586) 
(list 4480.5346 871.4689) 
(list 4480.5346 871.4792) 
(list 4480.5346 871.4894) 
(list 4480.5346 871.4997) 
(list 4480.5346 871.51) 
(list 4481.106 871.51)))
(apply 'command (append '("pline") coords '("c")))
(setq tap14 (ssadd (entlast) tap14))
(command "_mirror" (entlast) "" "4480,900" "4480,901" "No")
(setq tap14 (ssadd (entlast) tap14))
(setq coords (list 
(list 4480 871.51) 
(list 4480.135 871.51) 
(list 4480.135 871.5203) 
(list 4480.135 871.5306) 
(list 4480.135 871.5408) 
(list 4480.135 871.5511) 
(list 4480.135 871.5614) 
(list 4480.135 871.5717) 
(list 4480.135 871.5819) 
(list 4480.135 871.5922) 
(list 4480.135 871.6025) 
(list 4480.135 871.6128) 
(list 4480.135 871.6231) 
(list 4480.135 871.6333) 
(list 4480.135 871.6436) 
(list 4480.135 871.6539) 
(list 4480.135 871.6642) 
(list 4480.135 871.6744) 
(list 4480.135 871.6847) 
(list 4480.135 871.695) 
(list 4480.135 871.7053) 
(list 4480.135 871.7156) 
(list 4480.135 871.7258) 
(list 4480.135 871.7361) 
(list 4480.135 871.7464) 
(list 4480.135 871.7567) 
(list 4480.135 871.7669) 
(list 4480.135 871.7772) 
(list 4480.135 871.7875) 
(list 4480.135 871.7978) 
(list 4480.135 871.8081) 
(list 4480.135 871.8183) 
(list 4480.135 871.8286) 
(list 4480.135 871.8389) 
(list 4480.135 871.8492) 
(list 4480.135 871.8594) 
(list 4480.135 871.8697) 
(list 4480.135 871.88) 
(list 4480 871.88)))
(apply 'command (append '("pline") coords '("c")))
(setq tap14 (ssadd (entlast) tap14))
(command "_mirror" (entlast) "" "4480,900" "4480,901" "No")
(setq tap14 (ssadd (entlast) tap14))
(setq coords (list 
(list 4480.5438 871.51) 
(list 4480.5346 871.51) 
(list 4480.5332 871.5203) 
(list 4480.5284 871.5306) 
(list 4480.5205 871.5408) 
(list 4480.5097 871.5511) 
(list 4480.4961 871.5614) 
(list 4480.4804 871.5717) 
(list 4480.4629 871.5819) 
(list 4480.4441 871.5922) 
(list 4480.4247 871.6025) 
(list 4480.4052 871.6128) 
(list 4480.3862 871.6231) 
(list 4480.3683 871.6333) 
(list 4480.3521 871.6436) 
(list 4480.338 871.6539) 
(list 4480.3265 871.6642) 
(list 4480.3179 871.6744) 
(list 4480.3125 871.6847) 
(list 4480.3106 871.695) 
(list 4480.3121 871.7053) 
(list 4480.3171 871.7156) 
(list 4480.3254 871.7258) 
(list 4480.3367 871.7361) 
(list 4480.3508 871.7464) 
(list 4480.3672 871.7567) 
(list 4480.3854 871.7669) 
(list 4480.4049 871.7772) 
(list 4480.4251 871.7875) 
(list 4480.4454 871.7978) 
(list 4480.4651 871.8081) 
(list 4480.4837 871.8183) 
(list 4480.5006 871.8286) 
(list 4480.5153 871.8389) 
(list 4480.5272 871.8492) 
(list 4480.5362 871.8594) 
(list 4480.5417 871.8697) 
(list 4480.5438 871.88) 
(list 4480.5438 871.88)))
(apply 'command (append '("pline") coords '("c")))
(setq tap14 (ssadd (entlast) tap14))
(command "_mirror" (entlast) "" "4480,900" "4480,901" "No")
(setq tap14 (ssadd (entlast) tap14))
(setq coords (list 
(list 4481.106 871.51) 
(list 4480.5438 871.51) 
(list 4480.5438 871.5203) 
(list 4480.5438 871.5306) 
(list 4480.5438 871.5408) 
(list 4480.5438 871.5511) 
(list 4480.5438 871.5614) 
(list 4480.5438 871.5717) 
(list 4480.5438 871.5819) 
(list 4480.5438 871.5922) 
(list 4480.5438 871.6025) 
(list 4480.5438 871.6128) 
(list 4480.5438 871.6231) 
(list 4480.5438 871.6333) 
(list 4480.5438 871.6436) 
(list 4480.5438 871.6539) 
(list 4480.5438 871.6642) 
(list 4480.5438 871.6744) 
(list 4480.5438 871.6847) 
(list 4480.5438 871.695) 
(list 4480.5438 871.7053) 
(list 4480.5438 871.7156) 
(list 4480.5438 871.7258) 
(list 4480.5438 871.7361) 
(list 4480.5438 871.7464) 
(list 4480.5438 871.7567) 
(list 4480.5438 871.7669) 
(list 4480.5438 871.7772) 
(list 4480.5438 871.7875) 
(list 4480.5438 871.7978) 
(list 4480.5438 871.8081) 
(list 4480.5438 871.8183) 
(list 4480.5438 871.8286) 
(list 4480.5438 871.8389) 
(list 4480.5438 871.8492) 
(list 4480.5438 871.8594) 
(list 4480.5438 871.8697) 
(list 4480.5438 871.88) 
(list 4481.106 871.88)))
(apply 'command (append '("pline") coords '("c")))
(setq tap14 (ssadd (entlast) tap14))
(command "_mirror" (entlast) "" "4480,900" "4480,901" "No")
(setq tap14 (ssadd (entlast) tap14))
(setq coords (list 
(list 4480 871.88) 
(list 4480.135 871.88) 
(list 4480.135 871.8903) 
(list 4480.135 871.9006) 
(list 4480.135 871.9108) 
(list 4480.135 871.9211) 
(list 4480.135 871.9314) 
(list 4480.135 871.9417) 
(list 4480.135 871.9519) 
(list 4480.135 871.9622) 
(list 4480.135 871.9725) 
(list 4480.135 871.9828) 
(list 4480.135 871.9931) 
(list 4480.135 872.0033) 
(list 4480.135 872.0136) 
(list 4480.135 872.0239) 
(list 4480.135 872.0342) 
(list 4480.135 872.0444) 
(list 4480.135 872.0547) 
(list 4480.135 872.065) 
(list 4480.135 872.0753) 
(list 4480.135 872.0856) 
(list 4480.135 872.0958) 
(list 4480.135 872.1061) 
(list 4480.135 872.1164) 
(list 4480.135 872.1267) 
(list 4480.135 872.1369) 
(list 4480.135 872.1472) 
(list 4480.135 872.1575) 
(list 4480.135 872.1678) 
(list 4480.135 872.1781) 
(list 4480.135 872.1883) 
(list 4480.135 872.1986) 
(list 4480.135 872.2089) 
(list 4480.135 872.2192) 
(list 4480.135 872.2294) 
(list 4480.135 872.2397) 
(list 4480.135 872.25) 
(list 4480 872.25)))
(apply 'command (append '("pline") coords '("c")))
(setq tap14 (ssadd (entlast) tap14))
(command "_mirror" (entlast) "" "4480,900" "4480,901" "No")
(setq tap14 (ssadd (entlast) tap14))
(setq coords (list 
(list 4480.553 871.88) 
(list 4480.5438 871.88) 
(list 4480.5423 871.8903) 
(list 4480.5371 871.9006) 
(list 4480.5286 871.9108) 
(list 4480.5169 871.9211) 
(list 4480.5023 871.9314) 
(list 4480.4854 871.9417) 
(list 4480.4665 871.9519) 
(list 4480.4463 871.9622) 
(list 4480.4254 871.9725) 
(list 4480.4045 871.9828) 
(list 4480.3841 871.9931) 
(list 4480.3648 872.0033) 
(list 4480.3474 872.0136) 
(list 4480.3322 872.0239) 
(list 4480.3199 872.0342) 
(list 4480.3107 872.0444) 
(list 4480.3049 872.0547) 
(list 4480.3029 872.065) 
(list 4480.3045 872.0753) 
(list 4480.3099 872.0856) 
(list 4480.3188 872.0958) 
(list 4480.3309 872.1061) 
(list 4480.3461 872.1164) 
(list 4480.3637 872.1267) 
(list 4480.3832 872.1369) 
(list 4480.4042 872.1472) 
(list 4480.4258 872.1575) 
(list 4480.4476 872.1678) 
(list 4480.4687 872.1781) 
(list 4480.4887 872.1883) 
(list 4480.5068 872.1986) 
(list 4480.5225 872.2089) 
(list 4480.5353 872.2192) 
(list 4480.5449 872.2294) 
(list 4480.5508 872.2397) 
(list 4480.553 872.25) 
(list 4480.553 872.25)))
(apply 'command (append '("pline") coords '("c")))
(setq tap14 (ssadd (entlast) tap14))
(command "_mirror" (entlast) "" "4480,900" "4480,901" "No")
(setq tap14 (ssadd (entlast) tap14))
(setq coords (list 
(list 4481.106 871.88) 
(list 4480.553 871.88) 
(list 4480.553 871.8903) 
(list 4480.553 871.9006) 
(list 4480.553 871.9108) 
(list 4480.553 871.9211) 
(list 4480.553 871.9314) 
(list 4480.553 871.9417) 
(list 4480.553 871.9519) 
(list 4480.553 871.9622) 
(list 4480.553 871.9725) 
(list 4480.553 871.9828) 
(list 4480.553 871.9931) 
(list 4480.553 872.0033) 
(list 4480.553 872.0136) 
(list 4480.553 872.0239) 
(list 4480.553 872.0342) 
(list 4480.553 872.0444) 
(list 4480.553 872.0547) 
(list 4480.553 872.065) 
(list 4480.553 872.0753) 
(list 4480.553 872.0856) 
(list 4480.553 872.0958) 
(list 4480.553 872.1061) 
(list 4480.553 872.1164) 
(list 4480.553 872.1267) 
(list 4480.553 872.1369) 
(list 4480.553 872.1472) 
(list 4480.553 872.1575) 
(list 4480.553 872.1678) 
(list 4480.553 872.1781) 
(list 4480.553 872.1883) 
(list 4480.553 872.1986) 
(list 4480.553 872.2089) 
(list 4480.553 872.2192) 
(list 4480.553 872.2294) 
(list 4480.553 872.2397) 
(list 4480.553 872.25) 
(list 4481.106 872.25)))
(apply 'command (append '("pline") coords '("c")))
(setq tap14 (ssadd (entlast) tap14))
(command "_mirror" (entlast) "" "4480,900" "4480,901" "No")
(setq tap14 (ssadd (entlast) tap14))
(command "_block" "blktap14" "4480,900" tap14 "")
(command "_insert" "blktap14" "4480,900" "1" "1" "0")
(command "_insert" "blktap14" "4480,900" "1" "1" "180")
(setq uc14 nil)
(setq uc14 (ssadd))
(setq coords (list 
(list 0 -0.185) 
(list 0.135 -0.185) 
(list 0.135 -0.17472) 
(list 0.135 -0.16444) 
(list 0.135 -0.15417) 
(list 0.135 -0.14389) 
(list 0.135 -0.13361) 
(list 0.135 -0.12333) 
(list 0.135 -0.11306) 
(list 0.135 -0.10278) 
(list 0.135 -0.0925) 
(list 0.135 -0.082222) 
(list 0.135 -0.071944) 
(list 0.135 -0.061667) 
(list 0.135 -0.051389) 
(list 0.135 -0.041111) 
(list 0.135 -0.030833) 
(list 0.135 -0.020556) 
(list 0.135 -0.010278) 
(list 0.135 0) 
(list 0.135 0.010278) 
(list 0.135 0.020556) 
(list 0.135 0.030833) 
(list 0.135 0.041111) 
(list 0.135 0.051389) 
(list 0.135 0.061667) 
(list 0.135 0.071944) 
(list 0.135 0.082222) 
(list 0.135 0.0925) 
(list 0.135 0.10278) 
(list 0.135 0.11306) 
(list 0.135 0.12333) 
(list 0.135 0.13361) 
(list 0.135 0.14389) 
(list 0.135 0.15417) 
(list 0.135 0.16444) 
(list 0.135 0.17472) 
(list 0.135 0.185) 
(list 0 0.185)))
(apply 'command (append '("pline") coords '("c")))
(setq uc14 (ssadd (entlast) uc14))
(setq coords (list 
(list 1.106 -0.185) 
(list 0.553 -0.185) 
(list 0.55107 -0.17472) 
(list 0.54534 -0.16444) 
(list 0.53599 -0.15417) 
(list 0.52329 -0.14389) 
(list 0.50763 -0.13361) 
(list 0.4895 -0.12333) 
(list 0.46944 -0.11306) 
(list 0.44805 -0.10278) 
(list 0.426 -0.0925) 
(list 0.40395 -0.082222) 
(list 0.38256 -0.071944) 
(list 0.3625 -0.061667) 
(list 0.34437 -0.051389) 
(list 0.32871 -0.041111) 
(list 0.31601 -0.030833) 
(list 0.30666 -0.020556) 
(list 0.30093 -0.010278) 
(list 0.299 0) 
(list 0.30093 0.010278) 
(list 0.30666 0.020556) 
(list 0.31601 0.030833) 
(list 0.32871 0.041111) 
(list 0.34437 0.051389) 
(list 0.3625 0.061667) 
(list 0.38256 0.071944) 
(list 0.40395 0.082222) 
(list 0.426 0.0925) 
(list 0.44805 0.10278) 
(list 0.46944 0.11306) 
(list 0.4895 0.12333) 
(list 0.50763 0.13361) 
(list 0.52329 0.14389) 
(list 0.53599 0.15417) 
(list 0.54534 0.16444) 
(list 0.55107 0.17472) 
(list 0.553 0.185) 
(list 1.106 0.185)))
(apply 'command (append '("pline") coords '("c")))
(setq uc14 (ssadd (entlast) uc14))
(command "_block" "blkuc14" "0,0.185" uc14 "")
(command "_insert" "blkuc14" "4480,872.62" "1" "1" "0")
(command "_insert" "blkuc14" "4480,872.25" "1" "1" "180")
(command "_insert" "blkuc14" "4480,872.99" "1" "1" "0")
(command "_insert" "blkuc14" "4480,872.62" "1" "1" "180")
(command "_insert" "blkuc14" "4480,873.36" "1" "1" "0")
(command "_insert" "blkuc14" "4480,872.99" "1" "1" "180")
(command "_insert" "blkuc14" "4480,873.73" "1" "1" "0")
(command "_insert" "blkuc14" "4480,873.36" "1" "1" "180")
(command "_insert" "blkuc14" "4480,874.1" "1" "1" "0")
(command "_insert" "blkuc14" "4480,873.73" "1" "1" "180")
(command "_insert" "blkuc14" "4480,874.47" "1" "1" "0")
(command "_insert" "blkuc14" "4480,874.1" "1" "1" "180")
(command "_insert" "blkuc14" "4480,874.84" "1" "1" "0")
(command "_insert" "blkuc14" "4480,874.47" "1" "1" "180")
(command "_insert" "blkuc14" "4480,875.21" "1" "1" "0")
(command "_insert" "blkuc14" "4480,874.84" "1" "1" "180")
(command "_insert" "blkuc14" "4480,875.58" "1" "1" "0")
(command "_insert" "blkuc14" "4480,875.21" "1" "1" "180")
(command "_insert" "blkuc14" "4480,875.95" "1" "1" "0")
(command "_insert" "blkuc14" "4480,875.58" "1" "1" "180")
(command "_insert" "blkuc14" "4480,876.32" "1" "1" "0")
(command "_insert" "blkuc14" "4480,875.95" "1" "1" "180")
(command "_insert" "blkuc14" "4480,876.69" "1" "1" "0")
(command "_insert" "blkuc14" "4480,876.32" "1" "1" "180")
(command "_insert" "blkuc14" "4480,877.06" "1" "1" "0")
(command "_insert" "blkuc14" "4480,876.69" "1" "1" "180")
(command "_insert" "blkuc14" "4480,877.43" "1" "1" "0")
(command "_insert" "blkuc14" "4480,877.06" "1" "1" "180")
(command "_insert" "blkuc14" "4480,877.8" "1" "1" "0")
(command "_insert" "blkuc14" "4480,877.43" "1" "1" "180")
(command "_insert" "blkuc14" "4480,878.17" "1" "1" "0")
(command "_insert" "blkuc14" "4480,877.8" "1" "1" "180")
(command "_insert" "blkuc14" "4480,878.54" "1" "1" "0")
(command "_insert" "blkuc14" "4480,878.17" "1" "1" "180")
(command "_insert" "blkuc14" "4480,878.91" "1" "1" "0")
(command "_insert" "blkuc14" "4480,878.54" "1" "1" "180")
(command "_insert" "blkuc14" "4480,879.28" "1" "1" "0")
(command "_insert" "blkuc14" "4480,878.91" "1" "1" "180")
(command "_insert" "blkuc14" "4480,879.65" "1" "1" "0")
(command "_insert" "blkuc14" "4480,879.28" "1" "1" "180")
(command "_insert" "blkuc14" "4480,880.02" "1" "1" "0")
(command "_insert" "blkuc14" "4480,879.65" "1" "1" "180")
(command "_insert" "blkuc14" "4480,880.39" "1" "1" "0")
(command "_insert" "blkuc14" "4480,880.02" "1" "1" "180")
(command "_insert" "blkuc14" "4480,880.76" "1" "1" "0")
(command "_insert" "blkuc14" "4480,880.39" "1" "1" "180")
(command "_insert" "blkuc14" "4480,881.13" "1" "1" "0")
(command "_insert" "blkuc14" "4480,880.76" "1" "1" "180")
(command "_insert" "blkuc14" "4480,881.5" "1" "1" "0")
(command "_insert" "blkuc14" "4480,881.13" "1" "1" "180")
(command "_insert" "blkuc14" "4480,881.87" "1" "1" "0")
(command "_insert" "blkuc14" "4480,881.5" "1" "1" "180")
(command "_insert" "blkuc14" "4480,882.24" "1" "1" "0")
(command "_insert" "blkuc14" "4480,881.87" "1" "1" "180")
(command "_insert" "blkuc14" "4480,882.61" "1" "1" "0")
(command "_insert" "blkuc14" "4480,882.24" "1" "1" "180")
(command "_insert" "blkuc14" "4480,882.98" "1" "1" "0")
(command "_insert" "blkuc14" "4480,882.61" "1" "1" "180")
(command "_insert" "blkuc14" "4480,883.35" "1" "1" "0")
(command "_insert" "blkuc14" "4480,882.98" "1" "1" "180")
(command "_insert" "blkuc14" "4480,883.72" "1" "1" "0")
(command "_insert" "blkuc14" "4480,883.35" "1" "1" "180")
(command "_insert" "blkuc14" "4480,884.09" "1" "1" "0")
(command "_insert" "blkuc14" "4480,883.72" "1" "1" "180")
(command "_insert" "blkuc14" "4480,884.46" "1" "1" "0")
(command "_insert" "blkuc14" "4480,884.09" "1" "1" "180")
(command "_insert" "blkuc14" "4480,884.83" "1" "1" "0")
(command "_insert" "blkuc14" "4480,884.46" "1" "1" "180")
(command "_insert" "blkuc14" "4480,885.2" "1" "1" "0")
(command "_insert" "blkuc14" "4480,884.83" "1" "1" "180")
(command "_insert" "blkuc14" "4480,885.57" "1" "1" "0")
(command "_insert" "blkuc14" "4480,885.2" "1" "1" "180")
(command "_insert" "blkuc14" "4480,885.94" "1" "1" "0")
(command "_insert" "blkuc14" "4480,885.57" "1" "1" "180")
(command "_insert" "blkuc14" "4480,886.31" "1" "1" "0")
(command "_insert" "blkuc14" "4480,885.94" "1" "1" "180")
(command "_insert" "blkuc14" "4480,886.68" "1" "1" "0")
(command "_insert" "blkuc14" "4480,886.31" "1" "1" "180")
(command "_insert" "blkuc14" "4480,887.05" "1" "1" "0")
(command "_insert" "blkuc14" "4480,886.68" "1" "1" "180")
(command "_insert" "blkuc14" "4480,887.42" "1" "1" "0")
(command "_insert" "blkuc14" "4480,887.05" "1" "1" "180")
(command "_insert" "blkuc14" "4480,887.79" "1" "1" "0")
(command "_insert" "blkuc14" "4480,887.42" "1" "1" "180")
(command "_insert" "blkuc14" "4480,888.16" "1" "1" "0")
(command "_insert" "blkuc14" "4480,887.79" "1" "1" "180")
(command "_insert" "blkuc14" "4480,888.53" "1" "1" "0")
(command "_insert" "blkuc14" "4480,888.16" "1" "1" "180")
(command "_insert" "blkuc14" "4480,888.9" "1" "1" "0")
(command "_insert" "blkuc14" "4480,888.53" "1" "1" "180")
(command "_insert" "blkuc14" "4480,889.27" "1" "1" "0")
(command "_insert" "blkuc14" "4480,888.9" "1" "1" "180")
(command "_insert" "blkuc14" "4480,889.64" "1" "1" "0")
(command "_insert" "blkuc14" "4480,889.27" "1" "1" "180")
(command "_insert" "blkuc14" "4480,890.01" "1" "1" "0")
(command "_insert" "blkuc14" "4480,889.64" "1" "1" "180")
(command "_insert" "blkuc14" "4480,890.38" "1" "1" "0")
(command "_insert" "blkuc14" "4480,890.01" "1" "1" "180")
(command "_insert" "blkuc14" "4480,890.75" "1" "1" "0")
(command "_insert" "blkuc14" "4480,890.38" "1" "1" "180")
(command "_insert" "blkuc14" "4480,891.12" "1" "1" "0")
(command "_insert" "blkuc14" "4480,890.75" "1" "1" "180")
(command "_insert" "blkuc14" "4480,891.49" "1" "1" "0")
(command "_insert" "blkuc14" "4480,891.12" "1" "1" "180")
(command "_insert" "blkuc14" "4480,891.86" "1" "1" "0")
(command "_insert" "blkuc14" "4480,891.49" "1" "1" "180")
(command "_insert" "blkuc14" "4480,892.23" "1" "1" "0")
(command "_insert" "blkuc14" "4480,891.86" "1" "1" "180")
(command "_insert" "blkuc14" "4480,892.6" "1" "1" "0")
(command "_insert" "blkuc14" "4480,892.23" "1" "1" "180")
(command "_insert" "blkuc14" "4480,892.97" "1" "1" "0")
(command "_insert" "blkuc14" "4480,892.6" "1" "1" "180")
(command "_insert" "blkuc14" "4480,893.34" "1" "1" "0")
(command "_insert" "blkuc14" "4480,892.97" "1" "1" "180")
(command "_insert" "blkuc14" "4480,893.71" "1" "1" "0")
(command "_insert" "blkuc14" "4480,893.34" "1" "1" "180")
(command "_insert" "blkuc14" "4480,894.08" "1" "1" "0")
(command "_insert" "blkuc14" "4480,893.71" "1" "1" "180")
(command "_insert" "blkuc14" "4480,894.45" "1" "1" "0")
(command "_insert" "blkuc14" "4480,894.08" "1" "1" "180")
(command "_insert" "blkuc14" "4480,894.82" "1" "1" "0")
(command "_insert" "blkuc14" "4480,894.45" "1" "1" "180")
(command "_insert" "blkuc14" "4480,895.19" "1" "1" "0")
(command "_insert" "blkuc14" "4480,894.82" "1" "1" "180")
(command "_insert" "blkuc14" "4480,895.56" "1" "1" "0")
(command "_insert" "blkuc14" "4480,895.19" "1" "1" "180")
(command "_insert" "blkuc14" "4480,895.93" "1" "1" "0")
(command "_insert" "blkuc14" "4480,895.56" "1" "1" "180")
(command "_insert" "blkuc14" "4480,896.3" "1" "1" "0")
(command "_insert" "blkuc14" "4480,895.93" "1" "1" "180")
(command "_insert" "blkuc14" "4480,896.67" "1" "1" "0")
(command "_insert" "blkuc14" "4480,896.3" "1" "1" "180")
(command "_insert" "blkuc14" "4480,897.04" "1" "1" "0")
(command "_insert" "blkuc14" "4480,896.67" "1" "1" "180")
(command "_insert" "blkuc14" "4480,897.41" "1" "1" "0")
(command "_insert" "blkuc14" "4480,897.04" "1" "1" "180")
(command "_insert" "blkuc14" "4480,897.78" "1" "1" "0")
(command "_insert" "blkuc14" "4480,897.41" "1" "1" "180")
(command "_insert" "blkuc14" "4480,898.15" "1" "1" "0")
(command "_insert" "blkuc14" "4480,897.78" "1" "1" "180")
(command "_insert" "blkuc14" "4480,898.52" "1" "1" "0")
(command "_insert" "blkuc14" "4480,898.15" "1" "1" "180")
(command "_insert" "blkuc14" "4480,898.89" "1" "1" "0")
(command "_insert" "blkuc14" "4480,898.52" "1" "1" "180")
(command "_insert" "blkuc14" "4480,899.26" "1" "1" "0")
(command "_insert" "blkuc14" "4480,898.89" "1" "1" "180")
(command "_insert" "blkuc14" "4480,899.63" "1" "1" "0")
(command "_insert" "blkuc14" "4480,899.26" "1" "1" "180")
(command "_insert" "blkuc14" "4480,900" "1" "1" "0")
(command "_insert" "blkuc14" "4480,899.63" "1" "1" "180")
(command "_insert" "blkuc14" "4480,900.37" "1" "1" "0")
(command "_insert" "blkuc14" "4480,900" "1" "1" "180")
(command "_insert" "blkuc14" "4480,900.74" "1" "1" "0")
(command "_insert" "blkuc14" "4480,900.37" "1" "1" "180")
(command "_insert" "blkuc14" "4480,901.11" "1" "1" "0")
(command "_insert" "blkuc14" "4480,900.74" "1" "1" "180")
(command "_insert" "blkuc14" "4480,901.48" "1" "1" "0")
(command "_insert" "blkuc14" "4480,901.11" "1" "1" "180")
(command "_insert" "blkuc14" "4480,901.85" "1" "1" "0")
(command "_insert" "blkuc14" "4480,901.48" "1" "1" "180")
(command "_insert" "blkuc14" "4480,902.22" "1" "1" "0")
(command "_insert" "blkuc14" "4480,901.85" "1" "1" "180")
(command "_insert" "blkuc14" "4480,902.59" "1" "1" "0")
(command "_insert" "blkuc14" "4480,902.22" "1" "1" "180")
(command "_insert" "blkuc14" "4480,902.96" "1" "1" "0")
(command "_insert" "blkuc14" "4480,902.59" "1" "1" "180")
(command "_insert" "blkuc14" "4480,903.33" "1" "1" "0")
(command "_insert" "blkuc14" "4480,902.96" "1" "1" "180")
(command "_insert" "blkuc14" "4480,903.7" "1" "1" "0")
(command "_insert" "blkuc14" "4480,903.33" "1" "1" "180")
(command "_insert" "blkuc14" "4480,904.07" "1" "1" "0")
(command "_insert" "blkuc14" "4480,903.7" "1" "1" "180")
(command "_insert" "blkuc14" "4480,904.44" "1" "1" "0")
(command "_insert" "blkuc14" "4480,904.07" "1" "1" "180")
(command "_insert" "blkuc14" "4480,904.81" "1" "1" "0")
(command "_insert" "blkuc14" "4480,904.44" "1" "1" "180")
(command "_insert" "blkuc14" "4480,905.18" "1" "1" "0")
(command "_insert" "blkuc14" "4480,904.81" "1" "1" "180")
(command "_insert" "blkuc14" "4480,905.55" "1" "1" "0")
(command "_insert" "blkuc14" "4480,905.18" "1" "1" "180")
(command "_insert" "blkuc14" "4480,905.92" "1" "1" "0")
(command "_insert" "blkuc14" "4480,905.55" "1" "1" "180")
(command "_insert" "blkuc14" "4480,906.29" "1" "1" "0")
(command "_insert" "blkuc14" "4480,905.92" "1" "1" "180")
(command "_insert" "blkuc14" "4480,906.66" "1" "1" "0")
(command "_insert" "blkuc14" "4480,906.29" "1" "1" "180")
(command "_insert" "blkuc14" "4480,907.03" "1" "1" "0")
(command "_insert" "blkuc14" "4480,906.66" "1" "1" "180")
(command "_insert" "blkuc14" "4480,907.4" "1" "1" "0")
(command "_insert" "blkuc14" "4480,907.03" "1" "1" "180")
(command "_insert" "blkuc14" "4480,907.77" "1" "1" "0")
(command "_insert" "blkuc14" "4480,907.4" "1" "1" "180")
(command "_insert" "blkuc14" "4480,908.14" "1" "1" "0")
(command "_insert" "blkuc14" "4480,907.77" "1" "1" "180")
(command "_insert" "blkuc14" "4480,908.51" "1" "1" "0")
(command "_insert" "blkuc14" "4480,908.14" "1" "1" "180")
(command "_insert" "blkuc14" "4480,908.88" "1" "1" "0")
(command "_insert" "blkuc14" "4480,908.51" "1" "1" "180")
(command "_insert" "blkuc14" "4480,909.25" "1" "1" "0")
(command "_insert" "blkuc14" "4480,908.88" "1" "1" "180")
(command "_insert" "blkuc14" "4480,909.62" "1" "1" "0")
(command "_insert" "blkuc14" "4480,909.25" "1" "1" "180")
(command "_insert" "blkuc14" "4480,909.99" "1" "1" "0")
(command "_insert" "blkuc14" "4480,909.62" "1" "1" "180")
(command "_insert" "blkuc14" "4480,910.36" "1" "1" "0")
(command "_insert" "blkuc14" "4480,909.99" "1" "1" "180")
(command "_insert" "blkuc14" "4480,910.73" "1" "1" "0")
(command "_insert" "blkuc14" "4480,910.36" "1" "1" "180")
(command "_insert" "blkuc14" "4480,911.1" "1" "1" "0")
(command "_insert" "blkuc14" "4480,910.73" "1" "1" "180")
(command "_insert" "blkuc14" "4480,911.47" "1" "1" "0")
(command "_insert" "blkuc14" "4480,911.1" "1" "1" "180")
(command "_insert" "blkuc14" "4480,911.84" "1" "1" "0")
(command "_insert" "blkuc14" "4480,911.47" "1" "1" "180")
(command "_insert" "blkuc14" "4480,912.21" "1" "1" "0")
(command "_insert" "blkuc14" "4480,911.84" "1" "1" "180")
(command "_insert" "blkuc14" "4480,912.58" "1" "1" "0")
(command "_insert" "blkuc14" "4480,912.21" "1" "1" "180")
(command "_insert" "blkuc14" "4480,912.95" "1" "1" "0")
(command "_insert" "blkuc14" "4480,912.58" "1" "1" "180")
(command "_insert" "blkuc14" "4480,913.32" "1" "1" "0")
(command "_insert" "blkuc14" "4480,912.95" "1" "1" "180")
(command "_insert" "blkuc14" "4480,913.69" "1" "1" "0")
(command "_insert" "blkuc14" "4480,913.32" "1" "1" "180")
(command "_insert" "blkuc14" "4480,914.06" "1" "1" "0")
(command "_insert" "blkuc14" "4480,913.69" "1" "1" "180")
(command "_insert" "blkuc14" "4480,914.43" "1" "1" "0")
(command "_insert" "blkuc14" "4480,914.06" "1" "1" "180")
(command "_insert" "blkuc14" "4480,914.8" "1" "1" "0")
(command "_insert" "blkuc14" "4480,914.43" "1" "1" "180")
(command "_insert" "blkuc14" "4480,915.17" "1" "1" "0")
(command "_insert" "blkuc14" "4480,914.8" "1" "1" "180")
(command "_insert" "blkuc14" "4480,915.54" "1" "1" "0")
(command "_insert" "blkuc14" "4480,915.17" "1" "1" "180")
(command "_insert" "blkuc14" "4480,915.91" "1" "1" "0")
(command "_insert" "blkuc14" "4480,915.54" "1" "1" "180")
(command "_insert" "blkuc14" "4480,916.28" "1" "1" "0")
(command "_insert" "blkuc14" "4480,915.91" "1" "1" "180")
(command "_insert" "blkuc14" "4480,916.65" "1" "1" "0")
(command "_insert" "blkuc14" "4480,916.28" "1" "1" "180")
(command "_insert" "blkuc14" "4480,917.02" "1" "1" "0")
(command "_insert" "blkuc14" "4480,916.65" "1" "1" "180")
(command "_insert" "blkuc14" "4480,917.39" "1" "1" "0")
(command "_insert" "blkuc14" "4480,917.02" "1" "1" "180")
(command "_insert" "blkuc14" "4480,917.76" "1" "1" "0")
(command "_insert" "blkuc14" "4480,917.39" "1" "1" "180")
(command "_insert" "blkuc14" "4480,918.13" "1" "1" "0")
(command "_insert" "blkuc14" "4480,917.76" "1" "1" "180")
(command "_insert" "blkuc14" "4480,918.5" "1" "1" "0")
(command "_insert" "blkuc14" "4480,918.13" "1" "1" "180")
(command "_insert" "blkuc14" "4480,918.87" "1" "1" "0")
(command "_insert" "blkuc14" "4480,918.5" "1" "1" "180")
(command "_insert" "blkuc14" "4480,919.24" "1" "1" "0")
(command "_insert" "blkuc14" "4480,918.87" "1" "1" "180")
(command "_insert" "blkuc14" "4480,919.61" "1" "1" "0")
(command "_insert" "blkuc14" "4480,919.24" "1" "1" "180")
(command "_insert" "blkuc14" "4480,919.98" "1" "1" "0")
(command "_insert" "blkuc14" "4480,919.61" "1" "1" "180")
(command "_insert" "blkuc14" "4480,920.35" "1" "1" "0")
(command "_insert" "blkuc14" "4480,919.98" "1" "1" "180")
(command "_insert" "blkuc14" "4480,920.72" "1" "1" "0")
(command "_insert" "blkuc14" "4480,920.35" "1" "1" "180")
(command "_insert" "blkuc14" "4480,921.09" "1" "1" "0")
(command "_insert" "blkuc14" "4480,920.72" "1" "1" "180")
(command "_insert" "blkuc14" "4480,921.46" "1" "1" "0")
(command "_insert" "blkuc14" "4480,921.09" "1" "1" "180")
(command "_insert" "blkuc14" "4480,921.83" "1" "1" "0")
(command "_insert" "blkuc14" "4480,921.46" "1" "1" "180")
(command "_insert" "blkuc14" "4480,922.2" "1" "1" "0")
(command "_insert" "blkuc14" "4480,921.83" "1" "1" "180")
(command "_insert" "blkuc14" "4480,922.57" "1" "1" "0")
(command "_insert" "blkuc14" "4480,922.2" "1" "1" "180")
(command "_insert" "blkuc14" "4480,922.94" "1" "1" "0")
(command "_insert" "blkuc14" "4480,922.57" "1" "1" "180")
(command "_insert" "blkuc14" "4480,923.31" "1" "1" "0")
(command "_insert" "blkuc14" "4480,922.94" "1" "1" "180")
(command "_insert" "blkuc14" "4480,923.68" "1" "1" "0")
(command "_insert" "blkuc14" "4480,923.31" "1" "1" "180")
(command "_insert" "blkuc14" "4480,924.05" "1" "1" "0")
(command "_insert" "blkuc14" "4480,923.68" "1" "1" "180")
(command "_insert" "blkuc14" "4480,924.42" "1" "1" "0")
(command "_insert" "blkuc14" "4480,924.05" "1" "1" "180")
(command "_insert" "blkuc14" "4480,924.79" "1" "1" "0")
(command "_insert" "blkuc14" "4480,924.42" "1" "1" "180")
(command "_insert" "blkuc14" "4480,925.16" "1" "1" "0")
(command "_insert" "blkuc14" "4480,924.79" "1" "1" "180")
(command "_insert" "blkuc14" "4480,925.53" "1" "1" "0")
(command "_insert" "blkuc14" "4480,925.16" "1" "1" "180")
(command "_insert" "blkuc14" "4480,925.9" "1" "1" "0")
(command "_insert" "blkuc14" "4480,925.53" "1" "1" "180")
(command "_insert" "blkuc14" "4480,926.27" "1" "1" "0")
(command "_insert" "blkuc14" "4480,925.9" "1" "1" "180")
(command "_insert" "blkuc14" "4480,926.64" "1" "1" "0")
(command "_insert" "blkuc14" "4480,926.27" "1" "1" "180")
(command "_insert" "blkuc14" "4480,927.01" "1" "1" "0")
(command "_insert" "blkuc14" "4480,926.64" "1" "1" "180")
(command "_insert" "blkuc14" "4480,927.38" "1" "1" "0")
(command "_insert" "blkuc14" "4480,927.01" "1" "1" "180")
(command "_insert" "blkuc14" "4480,927.75" "1" "1" "0")
(command "_insert" "blkuc14" "4480,927.38" "1" "1" "180")
(command "_layer" "set" "phccover" "")
(command "_rectangle" "4478.894,933.3" "4481.106,866.7")
(command "_layer" "set" "nitride" "")
(setq phc14 currobj)
(command "_layer" "set" "cover" "")
(command "_rectangle" "4478.894,836.7" "4481.106,963.3")
(command "_layer" "set" "nitride" "")
(command "_layer" "set" "text" "")
(command "_circle" "4477.944,846.7" "0.075")
(command "_circle" "4477.569,846.7" "0.15")
(command "_circle" "4477.194,846.7" "0.075")
(command "_circle" "4476.819,846.7" "0.15")
(command "_circle" "4477.944,848.7" "0.075")
(command "_circle" "4477.569,848.7" "0.075")
(command "_circle" "4477.194,848.7" "0.15")
(command "_circle" "4476.819,848.7" "0.15")
(command "_circle" "4477.944,850.7" "0.075")
(command "_circle" "4477.569,850.7" "0.15")
(command "_circle" "4477.194,850.7" "0.15")
(command "_circle" "4476.819,850.7" "0.15")
(command "_circle" "4477.944,852.7" "0.075")
(command "_circle" "4477.569,852.7" "0.075")
(command "_circle" "4477.194,852.7" "0.075")
(command "_circle" "4476.819,852.7" "0.075")
(command "_circle" "4476.444,852.7" "0.15")
(command "_circle" "4477.944,854.7" "0.075")
(command "_circle" "4477.569,854.7" "0.15")
(command "_circle" "4477.194,854.7" "0.075")
(command "_circle" "4476.819,854.7" "0.075")
(command "_circle" "4476.444,854.7" "0.15")
(command "_circle" "4477.944,856.7" "0.075")
(command "_circle" "4477.569,856.7" "0.075")
(command "_circle" "4477.194,856.7" "0.15")
(command "_circle" "4476.819,856.7" "0.075")
(command "_circle" "4476.444,856.7" "0.15")
(command "_circle" "4477.944,858.7" "0.075")
(command "_circle" "4477.569,858.7" "0.15")
(command "_circle" "4477.194,858.7" "0.15")
(command "_circle" "4476.819,858.7" "0.075")
(command "_circle" "4476.444,858.7" "0.15")
(command "_circle" "4477.944,860.7" "0.075")
(command "_circle" "4477.569,860.7" "0.075")
(command "_circle" "4477.194,860.7" "0.075")
(command "_circle" "4476.819,860.7" "0.15")
(command "_circle" "4476.444,860.7" "0.15")
(command "_circle" "4477.944,862.7" "0.075")
(command "_circle" "4477.569,862.7" "0.15")
(command "_circle" "4477.194,862.7" "0.075")
(command "_circle" "4476.819,862.7" "0.15")
(command "_circle" "4476.444,862.7" "0.15")
(command "_circle" "4477.944,864.7" "0.075")
(command "_circle" "4477.569,864.7" "0.075")
(command "_circle" "4477.194,864.7" "0.15")
(command "_circle" "4476.819,864.7" "0.15")
(command "_circle" "4476.444,864.7" "0.15")
(command "_circle" "4477.944,866.7" "0.075")
(command "_circle" "4477.569,866.7" "0.15")
(command "_circle" "4477.194,866.7" "0.15")
(command "_circle" "4476.819,866.7" "0.15")
(command "_circle" "4476.444,866.7" "0.15")
(command "_circle" "4477.944,868.7" "0.075")
(command "_circle" "4477.569,868.7" "0.075")
(command "_circle" "4477.194,868.7" "0.075")
(command "_circle" "4476.819,868.7" "0.075")
(command "_circle" "4476.444,868.7" "0.075")
(command "_circle" "4476.069,868.7" "0.15")
(command "_circle" "4477.944,870.7" "0.075")
(command "_circle" "4477.569,870.7" "0.15")
(command "_circle" "4477.194,870.7" "0.075")
(command "_circle" "4476.819,870.7" "0.075")
(command "_circle" "4476.444,870.7" "0.075")
(command "_circle" "4476.069,870.7" "0.15")
(command "_circle" "4477.944,872.7" "0.075")
(command "_circle" "4477.569,872.7" "0.075")
(command "_circle" "4477.194,872.7" "0.15")
(command "_circle" "4476.819,872.7" "0.075")
(command "_circle" "4476.444,872.7" "0.075")
(command "_circle" "4476.069,872.7" "0.15")
(command "_circle" "4477.944,874.7" "0.075")
(command "_circle" "4477.569,874.7" "0.15")
(command "_circle" "4477.194,874.7" "0.15")
(command "_circle" "4476.819,874.7" "0.075")
(command "_circle" "4476.444,874.7" "0.075")
(command "_circle" "4476.069,874.7" "0.15")
(command "_circle" "4477.944,876.7" "0.075")
(command "_circle" "4477.569,876.7" "0.075")
(command "_circle" "4477.194,876.7" "0.075")
(command "_circle" "4476.819,876.7" "0.15")
(command "_circle" "4476.444,876.7" "0.075")
(command "_circle" "4476.069,876.7" "0.15")
(command "_circle" "4477.944,878.7" "0.075")
(command "_circle" "4477.569,878.7" "0.15")
(command "_circle" "4477.194,878.7" "0.075")
(command "_circle" "4476.819,878.7" "0.15")
(command "_circle" "4476.444,878.7" "0.075")
(command "_circle" "4476.069,878.7" "0.15")
(command "_circle" "4477.944,880.7" "0.075")
(command "_circle" "4477.569,880.7" "0.075")
(command "_circle" "4477.194,880.7" "0.15")
(command "_circle" "4476.819,880.7" "0.15")
(command "_circle" "4476.444,880.7" "0.075")
(command "_circle" "4476.069,880.7" "0.15")
(command "_circle" "4477.944,882.7" "0.075")
(command "_circle" "4477.569,882.7" "0.15")
(command "_circle" "4477.194,882.7" "0.15")
(command "_circle" "4476.819,882.7" "0.15")
(command "_circle" "4476.444,882.7" "0.075")
(command "_circle" "4476.069,882.7" "0.15")
(command "_circle" "4477.944,884.7" "0.075")
(command "_circle" "4477.569,884.7" "0.075")
(command "_circle" "4477.194,884.7" "0.075")
(command "_circle" "4476.819,884.7" "0.075")
(command "_circle" "4476.444,884.7" "0.15")
(command "_circle" "4476.069,884.7" "0.15")
(command "_circle" "4477.944,886.7" "0.075")
(command "_circle" "4477.569,886.7" "0.15")
(command "_circle" "4477.194,886.7" "0.075")
(command "_circle" "4476.819,886.7" "0.075")
(command "_circle" "4476.444,886.7" "0.15")
(command "_circle" "4476.069,886.7" "0.15")
(command "_circle" "4477.944,888.7" "0.075")
(command "_circle" "4477.569,888.7" "0.075")
(command "_circle" "4477.194,888.7" "0.15")
(command "_circle" "4476.819,888.7" "0.075")
(command "_circle" "4476.444,888.7" "0.15")
(command "_circle" "4476.069,888.7" "0.15")
(command "_circle" "4477.944,890.7" "0.075")
(command "_circle" "4477.569,890.7" "0.15")
(command "_circle" "4477.194,890.7" "0.15")
(command "_circle" "4476.819,890.7" "0.075")
(command "_circle" "4476.444,890.7" "0.15")
(command "_circle" "4476.069,890.7" "0.15")
(command "_circle" "4477.944,892.7" "0.075")
(command "_circle" "4477.569,892.7" "0.075")
(command "_circle" "4477.194,892.7" "0.075")
(command "_circle" "4476.819,892.7" "0.15")
(command "_circle" "4476.444,892.7" "0.15")
(command "_circle" "4476.069,892.7" "0.15")
(command "_circle" "4477.944,894.7" "0.075")
(command "_circle" "4477.569,894.7" "0.15")
(command "_circle" "4477.194,894.7" "0.075")
(command "_circle" "4476.819,894.7" "0.15")
(command "_circle" "4476.444,894.7" "0.15")
(command "_circle" "4476.069,894.7" "0.15")
(command "_circle" "4477.944,896.7" "0.075")
(command "_circle" "4477.569,896.7" "0.075")
(command "_circle" "4477.194,896.7" "0.15")
(command "_circle" "4476.819,896.7" "0.15")
(command "_circle" "4476.444,896.7" "0.15")
(command "_circle" "4476.069,896.7" "0.15")
(command "_circle" "4477.944,898.7" "0.075")
(command "_circle" "4477.569,898.7" "0.15")
(command "_circle" "4477.194,898.7" "0.15")
(command "_circle" "4476.819,898.7" "0.15")
(command "_circle" "4476.444,898.7" "0.15")
(command "_circle" "4476.069,898.7" "0.15")
(command "_circle" "4477.944,900.7" "0.075")
(command "_circle" "4477.569,900.7" "0.075")
(command "_circle" "4477.194,900.7" "0.075")
(command "_circle" "4476.819,900.7" "0.075")
(command "_circle" "4476.444,900.7" "0.075")
(command "_circle" "4476.069,900.7" "0.075")
(command "_circle" "4475.694,900.7" "0.15")
(command "_circle" "4477.944,902.7" "0.075")
(command "_circle" "4477.569,902.7" "0.15")
(command "_circle" "4477.194,902.7" "0.075")
(command "_circle" "4476.819,902.7" "0.075")
(command "_circle" "4476.444,902.7" "0.075")
(command "_circle" "4476.069,902.7" "0.075")
(command "_circle" "4475.694,902.7" "0.15")
(command "_circle" "4477.944,904.7" "0.075")
(command "_circle" "4477.569,904.7" "0.075")
(command "_circle" "4477.194,904.7" "0.15")
(command "_circle" "4476.819,904.7" "0.075")
(command "_circle" "4476.444,904.7" "0.075")
(command "_circle" "4476.069,904.7" "0.075")
(command "_circle" "4475.694,904.7" "0.15")
(command "_circle" "4477.944,906.7" "0.075")
(command "_circle" "4477.569,906.7" "0.15")
(command "_circle" "4477.194,906.7" "0.15")
(command "_circle" "4476.819,906.7" "0.075")
(command "_circle" "4476.444,906.7" "0.075")
(command "_circle" "4476.069,906.7" "0.075")
(command "_circle" "4475.694,906.7" "0.15")
(command "_circle" "4477.944,908.7" "0.075")
(command "_circle" "4477.569,908.7" "0.075")
(command "_circle" "4477.194,908.7" "0.075")
(command "_circle" "4476.819,908.7" "0.15")
(command "_circle" "4476.444,908.7" "0.075")
(command "_circle" "4476.069,908.7" "0.075")
(command "_circle" "4475.694,908.7" "0.15")
(command "_circle" "4477.944,910.7" "0.075")
(command "_circle" "4477.569,910.7" "0.15")
(command "_circle" "4477.194,910.7" "0.075")
(command "_circle" "4476.819,910.7" "0.15")
(command "_circle" "4476.444,910.7" "0.075")
(command "_circle" "4476.069,910.7" "0.075")
(command "_circle" "4475.694,910.7" "0.15")
(command "_circle" "4477.944,912.7" "0.075")
(command "_circle" "4477.569,912.7" "0.075")
(command "_circle" "4477.194,912.7" "0.15")
(command "_circle" "4476.819,912.7" "0.15")
(command "_circle" "4476.444,912.7" "0.075")
(command "_circle" "4476.069,912.7" "0.075")
(command "_circle" "4475.694,912.7" "0.15")
(command "_circle" "4477.944,914.7" "0.075")
(command "_circle" "4477.569,914.7" "0.15")
(command "_circle" "4477.194,914.7" "0.15")
(command "_circle" "4476.819,914.7" "0.15")
(command "_circle" "4476.444,914.7" "0.075")
(command "_circle" "4476.069,914.7" "0.075")
(command "_circle" "4475.694,914.7" "0.15")
(command "_circle" "4477.944,916.7" "0.075")
(command "_circle" "4477.569,916.7" "0.075")
(command "_circle" "4477.194,916.7" "0.075")
(command "_circle" "4476.819,916.7" "0.075")
(command "_circle" "4476.444,916.7" "0.15")
(command "_circle" "4476.069,916.7" "0.075")
(command "_circle" "4475.694,916.7" "0.15")
(command "_circle" "4477.944,918.7" "0.075")
(command "_circle" "4477.569,918.7" "0.15")
(command "_circle" "4477.194,918.7" "0.075")
(command "_circle" "4476.819,918.7" "0.075")
(command "_circle" "4476.444,918.7" "0.15")
(command "_circle" "4476.069,918.7" "0.075")
(command "_circle" "4475.694,918.7" "0.15")
(command "_circle" "4477.944,920.7" "0.075")
(command "_circle" "4477.569,920.7" "0.075")
(command "_circle" "4477.194,920.7" "0.15")
(command "_circle" "4476.819,920.7" "0.075")
(command "_circle" "4476.444,920.7" "0.15")
(command "_circle" "4476.069,920.7" "0.075")
(command "_circle" "4475.694,920.7" "0.15")
(command "_circle" "4477.944,922.7" "0.075")
(command "_circle" "4477.569,922.7" "0.15")
(command "_circle" "4477.194,922.7" "0.15")
(command "_circle" "4476.819,922.7" "0.075")
(command "_circle" "4476.444,922.7" "0.15")
(command "_circle" "4476.069,922.7" "0.075")
(command "_circle" "4475.694,922.7" "0.15")
(command "_circle" "4477.944,924.7" "0.075")
(command "_circle" "4477.569,924.7" "0.075")
(command "_circle" "4477.194,924.7" "0.075")
(command "_circle" "4476.819,924.7" "0.15")
(command "_circle" "4476.444,924.7" "0.15")
(command "_circle" "4476.069,924.7" "0.075")
(command "_circle" "4475.694,924.7" "0.15")
(command "_circle" "4477.944,926.7" "0.075")
(command "_circle" "4477.569,926.7" "0.15")
(command "_circle" "4477.194,926.7" "0.075")
(command "_circle" "4476.819,926.7" "0.15")
(command "_circle" "4476.444,926.7" "0.15")
(command "_circle" "4476.069,926.7" "0.075")
(command "_circle" "4475.694,926.7" "0.15")
(command "_circle" "4477.944,928.7" "0.075")
(command "_circle" "4477.569,928.7" "0.075")
(command "_circle" "4477.194,928.7" "0.15")
(command "_circle" "4476.819,928.7" "0.15")
(command "_circle" "4476.444,928.7" "0.15")
(command "_circle" "4476.069,928.7" "0.075")
(command "_circle" "4475.694,928.7" "0.15")
(command "_circle" "4477.944,930.7" "0.075")
(command "_circle" "4477.569,930.7" "0.15")
(command "_circle" "4477.194,930.7" "0.15")
(command "_circle" "4476.819,930.7" "0.15")
(command "_circle" "4476.444,930.7" "0.15")
(command "_circle" "4476.069,930.7" "0.075")
(command "_circle" "4475.694,930.7" "0.15")
(command "_circle" "4477.944,932.7" "0.075")
(command "_circle" "4477.569,932.7" "0.075")
(command "_circle" "4477.194,932.7" "0.075")
(command "_circle" "4476.819,932.7" "0.075")
(command "_circle" "4476.444,932.7" "0.075")
(command "_circle" "4476.069,932.7" "0.15")
(command "_circle" "4475.694,932.7" "0.15")
(command "_circle" "4477.944,934.7" "0.075")
(command "_circle" "4477.569,934.7" "0.15")
(command "_circle" "4477.194,934.7" "0.075")
(command "_circle" "4476.819,934.7" "0.075")
(command "_circle" "4476.444,934.7" "0.075")
(command "_circle" "4476.069,934.7" "0.15")
(command "_circle" "4475.694,934.7" "0.15")
(command "_circle" "4477.944,936.7" "0.075")
(command "_circle" "4477.569,936.7" "0.075")
(command "_circle" "4477.194,936.7" "0.15")
(command "_circle" "4476.819,936.7" "0.075")
(command "_circle" "4476.444,936.7" "0.075")
(command "_circle" "4476.069,936.7" "0.15")
(command "_circle" "4475.694,936.7" "0.15")
(command "_circle" "4477.944,938.7" "0.075")
(command "_circle" "4477.569,938.7" "0.15")
(command "_circle" "4477.194,938.7" "0.15")
(command "_circle" "4476.819,938.7" "0.075")
(command "_circle" "4476.444,938.7" "0.075")
(command "_circle" "4476.069,938.7" "0.15")
(command "_circle" "4475.694,938.7" "0.15")
(command "_circle" "4477.944,940.7" "0.075")
(command "_circle" "4477.569,940.7" "0.075")
(command "_circle" "4477.194,940.7" "0.075")
(command "_circle" "4476.819,940.7" "0.15")
(command "_circle" "4476.444,940.7" "0.075")
(command "_circle" "4476.069,940.7" "0.15")
(command "_circle" "4475.694,940.7" "0.15")
(command "_circle" "4477.944,942.7" "0.075")
(command "_circle" "4477.569,942.7" "0.15")
(command "_circle" "4477.194,942.7" "0.075")
(command "_circle" "4476.819,942.7" "0.15")
(command "_circle" "4476.444,942.7" "0.075")
(command "_circle" "4476.069,942.7" "0.15")
(command "_circle" "4475.694,942.7" "0.15")
(command "_circle" "4477.944,944.7" "0.075")
(command "_circle" "4477.569,944.7" "0.075")
(command "_circle" "4477.194,944.7" "0.15")
(command "_circle" "4476.819,944.7" "0.15")
(command "_circle" "4476.444,944.7" "0.075")
(command "_circle" "4476.069,944.7" "0.15")
(command "_circle" "4475.694,944.7" "0.15")
(command "_circle" "4477.944,946.7" "0.075")
(command "_circle" "4477.569,946.7" "0.15")
(command "_circle" "4477.194,946.7" "0.15")
(command "_circle" "4476.819,946.7" "0.15")
(command "_circle" "4476.444,946.7" "0.075")
(command "_circle" "4476.069,946.7" "0.15")
(command "_circle" "4475.694,946.7" "0.15")
(command "_circle" "4477.944,948.7" "0.075")
(command "_circle" "4477.569,948.7" "0.075")
(command "_circle" "4477.194,948.7" "0.075")
(command "_circle" "4476.819,948.7" "0.075")
(command "_circle" "4476.444,948.7" "0.15")
(command "_circle" "4476.069,948.7" "0.15")
(command "_circle" "4475.694,948.7" "0.15")
(command "_circle" "4477.944,950.7" "0.075")
(command "_circle" "4477.569,950.7" "0.15")
(command "_circle" "4477.194,950.7" "0.075")
(command "_circle" "4476.819,950.7" "0.075")
(command "_circle" "4476.444,950.7" "0.15")
(command "_circle" "4476.069,950.7" "0.15")
(command "_circle" "4475.694,950.7" "0.15")
(command "_circle" "4477.944,952.7" "0.075")
(command "_circle" "4477.569,952.7" "0.075")
(command "_circle" "4477.194,952.7" "0.15")
(command "_circle" "4476.819,952.7" "0.075")
(command "_circle" "4476.444,952.7" "0.15")
(command "_circle" "4476.069,952.7" "0.15")
(command "_circle" "4475.694,952.7" "0.15")
(command "_circle" "4477.944,954.7" "0.075")
(command "_circle" "4477.569,954.7" "0.15")
(command "_circle" "4477.194,954.7" "0.15")
(command "_circle" "4476.819,954.7" "0.075")
(command "_circle" "4476.444,954.7" "0.15")
(command "_circle" "4476.069,954.7" "0.15")
(command "_circle" "4475.694,954.7" "0.15")
(command "_circle" "4477.944,956.7" "0.075")
(command "_circle" "4477.569,956.7" "0.075")
(command "_circle" "4477.194,956.7" "0.075")
(command "_circle" "4476.819,956.7" "0.15")
(command "_circle" "4476.444,956.7" "0.15")
(command "_circle" "4476.069,956.7" "0.15")
(command "_circle" "4475.694,956.7" "0.15")
(command "_circle" "4477.944,958.7" "0.075")
(command "_circle" "4477.569,958.7" "0.15")
(command "_circle" "4477.194,958.7" "0.075")
(command "_circle" "4476.819,958.7" "0.15")
(command "_circle" "4476.444,958.7" "0.15")
(command "_circle" "4476.069,958.7" "0.15")
(command "_circle" "4475.694,958.7" "0.15")
(command "_circle" "4477.944,960.7" "0.075")
(command "_circle" "4477.569,960.7" "0.075")
(command "_circle" "4477.194,960.7" "0.15")
(command "_circle" "4476.819,960.7" "0.15")
(command "_circle" "4476.444,960.7" "0.15")
(command "_circle" "4476.069,960.7" "0.15")
(command "_circle" "4475.694,960.7" "0.15")
(command "_circle" "4477.944,962.7" "0.075")
(command "_circle" "4477.569,962.7" "0.15")
(command "_circle" "4477.194,962.7" "0.15")
(command "_circle" "4476.819,962.7" "0.15")
(command "_circle" "4476.444,962.7" "0.15")
(command "_circle" "4476.069,962.7" "0.15")
(command "_circle" "4475.694,962.7" "0.15")
(command "_layer" "set" "nitride" "")
(command "_layer" "set" "text" "")
(command-s "_text" "4466.894,963.3" "2" "-90" "a = 370 nm" )
(sssetfirst nil (ssget "_L"))
(if (not (numberp (vl-string-search "Mac" (getvar "platform")))) (c:txtexp))
(command "_layer" "set" "nitride" "")
(command "_layer" "set" "text" "")
(command-s "_text" "4463.894,963.3" "2" "-90" "gap = 270 nm" )
(sssetfirst nil (ssget "_L"))
(if (not (numberp (vl-string-search "Mac" (getvar "platform")))) (c:txtexp))
(command "_layer" "set" "nitride" "")
(command "_layer" "set" "text" "")
(command-s "_text" "4460.894,963.3" "2" "-90" "amplitude = 127 nm" )
(sssetfirst nil (ssget "_L"))
(if (not (numberp (vl-string-search "Mac" (getvar "platform")))) (c:txtexp))
(command "_layer" "set" "nitride" "")
(command "_layer" "set" "text" "")
(command-s "_text" "4457.894,963.3" "2" "-90" "start width = 280 nm" )
(sssetfirst nil (ssget "_L"))
(if (not (numberp (vl-string-search "Mac" (getvar "platform")))) (c:txtexp))
(command "_layer" "set" "nitride" "")
(command "_layer" "set" "text" "")
(command-s "_text" "4454.894,963.3" "2" "-90" "width = 291 nm" )
(sssetfirst nil (ssget "_L"))
(if (not (numberp (vl-string-search "Mac" (getvar "platform")))) (c:txtexp))
(command "_layer" "set" "nitride" "")
(command "_layer" "set" "text" "")
(command-s "_text" "4451.894,963.3" "2" "-90" "taper: 15" )
(sssetfirst nil (ssget "_L"))
(if (not (numberp (vl-string-search "Mac" (getvar "platform")))) (c:txtexp))
(command "_layer" "set" "nitride" "")
(command "_layer" "set" "text" "")
(command-s "_text" "4448.894,963.3" "2" "-90" "nominal: 150" )
(sssetfirst nil (ssget "_L"))
(if (not (numberp (vl-string-search "Mac" (getvar "platform")))) (c:txtexp))
(command "_layer" "set" "nitride" "")
(command "_layer" "set" "indicators" "")
(setq coords (list 
(list 4400.415 940) 
(list 4400.415 920) 
(list 4380.415 900) 
(list 4400.415 880) 
(list 4400.415 860) 
(list 4400.415 900) 
(list 4400.415 887.0711) 
(list 4387.4861 900) 
(list 4400.415 912.9289) 
(list 4400.415 900)))
(apply 'command (append '("pline") coords '("c")))
(command "._fillet" "radius" "1" "._fillet" "P" (entlast))
(setq coords (list 
(list 4559.585 940) 
(list 4559.585 920) 
(list 4579.585 900) 
(list 4559.585 880) 
(list 4559.585 860) 
(list 4559.585 900) 
(list 4559.585 887.0711) 
(list 4572.5139 900) 
(list 4559.585 912.9289) 
(list 4559.585 900)))
(apply 'command (append '("pline") coords '("c")))
(command "._fillet" "radius" "1" "._fillet" "P" (entlast))
(command "_layer" "set" "holes" "")
(command "_circle" "4398.0629,914.1124" "0.5")
(command "_circle" "4395.7109,911.7603" "0.5")
(command "_circle" "4393.3588,909.4083" "0.5")
(command "_circle" "4391.0067,907.0562" "0.5")
(command "_circle" "4388.6547,904.7041" "0.5")
(command "_circle" "4386.3026,902.3521" "0.5")
(command "_circle" "4383.9505,900" "0.5")
(command "_circle" "4386.3026,897.6479" "0.5")
(command "_circle" "4388.6547,895.2959" "0.5")
(command "_circle" "4391.0067,892.9438" "0.5")
(command "_circle" "4393.3588,890.5917" "0.5")
(command "_circle" "4395.7109,888.2397" "0.5")
(command "_circle" "4398.0629,885.8876" "0.5")
(command "_circle" "4561.9371,914.1124" "0.5")
(command "_circle" "4564.2891,911.7603" "0.5")
(command "_circle" "4566.6412,909.4083" "0.5")
(command "_circle" "4568.9933,907.0562" "0.5")
(command "_circle" "4571.3453,904.7041" "0.5")
(command "_circle" "4573.6974,902.3521" "0.5")
(command "_circle" "4576.0495,900" "0.5")
(command "_circle" "4573.6974,897.6479" "0.5")
(command "_circle" "4571.3453,895.2959" "0.5")
(command "_circle" "4568.9933,892.9438" "0.5")
(command "_circle" "4566.6412,890.5917" "0.5")
(command "_circle" "4564.2891,888.2397" "0.5")
(command "_circle" "4561.9371,885.8876" "0.5")
(command "_layer" "set" "nitride" "")
(command "_block" "blkcoupler14" "4480,900" coupler14 "")
(command "_insert" "blkcoupler14" "4480,900" "1" "1" "0")
(command "_insert" "blkcoupler14" "4480,900" "1" "1" "180")
(command "_block" "blksinglenanobeam14" "4480,900" singlenanobeam14 "")
(command "_insert" "blksinglenanobeam14" "4480,900" "1" "1" "0")
(command "_insert" "blksinglenanobeam14" "4480,900" "1" "1" "180")
(command "_block" "blkanglednodearray14" "4480,900" anglednodearray14 "")
(command "_insert" "blkanglednodearray14" "4480,900" "1" "1" "0")
(command "_insert" "blkanglednodearray14" "4480,900" "1" "1" "180")
(command "_block" "blkcooledsinglenanobeam14" "4480,900" cooledsinglenanobeam14 "")
(command "_insert" "blkcooledsinglenanobeam14" "4480,900" "1" "1" "0")
(command "_insert" "blkcooledsinglenanobeam14" "4480,900" "1" "1" "180")
(command "_block" "blkyjunction14" "4480,900" yjunction14 "")
(command "_insert" "blkyjunction14" "4480,900" "1" "1" "0")
(command "_insert" "blkyjunction14" "4480,900" "1" "1" "180")
; DRAWING BULGING VEE GROOVE
(command "_layer" "set" "vgroove" "")
(setq coords (list 
(list 4405.415 -605) 
(list 4405.415 0) 
(list 4405.415 0) 
(list 4405.415 1800) 
(list 4405.415 1800) 
(list 4405.415 2405) 
(list 4554.585 2405) 
(list 4554.585 1800) 
(list 4554.585 1800) 
(list 4554.585 0) 
(list 4554.585 0) 
(list 4554.585 -605)))
(apply 'command (append '("pline") coords '("c")))
(command "._fillet" "radius" "0" "._fillet" "P" (entlast))
(command "_layer" "set" "window" "")
(command "_rectangle" "4405.415,-1935" "4554.585,-600")
(command "_rectangle" "4405.415,2400" "4554.585,5300")
(command "_layer" "set" "grid" "")
(command "_rectangle" "4406.415,-1934" "4429.9433,-1909.2133")
(command "_array" "last" "" "R" "75" "3" "25.7867" "24.5283")
(command "_rectangle" "4481,-1934" "4504.5283,-1909.2133")
(command "_array" "last" "" "R" "75" "3" "25.7867" "24.5283")
(command "_rectangle" "4406.415,1" "4429.9433,25.7")
(command "_array" "last" "" "R" "70" "3" "25.7" "24.5283")
(command "_rectangle" "4481,1" "4504.5283,25.7")
(command "_array" "last" "" "R" "70" "3" "25.7" "24.5283")
(command "_rectangle" "4406.415,1801" "4429.9433,1825.9185")
(command "_array" "last" "" "R" "135" "3" "25.9185" "24.5283")
(command "_rectangle" "4481,1801" "4504.5283,1825.9185")
(command "_array" "last" "" "R" "135" "3" "25.9185" "24.5283")
(command "_layer" "set" "vgrooveFDA" "")
(command "_rectangle" "4554.585,-2233" "4405.415,-1933")
(command "_layer" "set" "nitride" "")
(command "_layer" "set" "holes" "")
(command "_circle" "4557.085,331.5" "0.5")
(command "_array" "last" "" "R" "379" "1" "3" "2.5")
(command "_circle" "4402.915,331.5" "0.5")
(command "_array" "last" "" "R" "379" "1" "3" "-2.5")
(command "_layer" "set" "nitride" "")
(command "_layer" "set" "window" "")
(command "_layer" "set" "window" "")
(command "_rectangle" "4559.585,0" "4720.415,1800")
(command "._fillet" "radius" "20" "._fillet" "P" (entlast))
(command "_layer" "set" "grid" "")
(command "_rectangle" "4560.585,1" "4582.4179,25.7")
(command "_array" "last" "" "R" "70" "7" "25.7" "22.8329")
(command "_layer" "set" "nitride" "")
; DRAWING REGION LAYER
(command "_layer" "set" "regionLayer14" "")
(command "_rectangle" "4400,-460" "4560,2260")
(command "_layer" "set" "nitride" "")
(setq coupler14 nil)
(setq singlenanobeam14 nil)
(setq anglednodearray14 nil)
(setq cooledsinglenanobeam14 nil)
(setq yjunction14 nil)
; DEVICE #15
(command "_layer" "set" "window" "")
(command "_circle" "4712.915,-415" "5")
(command "_circle" "4712.915,-402.5" "5")
(command "_circle" "4712.915,-390" "5")
(command "_circle" "4712.915,-377.5" "5")
(command "_circle" "4700.415,-415" "5")
(command "_circle" "4700.415,-402.5" "5")
(command "_circle" "4700.415,-390" "5")
(command "_circle" "4700.415,-377.5" "5")
(command "_circle" "4687.915,-415" "5")
(command "_circle" "4687.915,-402.5" "5")
(command "_circle" "4687.915,-390" "5")
(command "_circle" "4687.915,-377.5" "5")
(command "_circle" "4675.415,-415" "5")
(command "_circle" "4675.415,-402.5" "5")
(command "_circle" "4675.415,-390" "5")
(command "_layer" "set" "nitride" "")
(setq currobj nil)
(setq currobj (ssadd))
; DRAWING COUPLER
(setq coords (list 
(list 4800.0615 -415) 
(list 4800.0615 -413) 
(list 4873.585 -413) 
(list 4873.585 -413) 
(list 4873.9677 -413.0761) 
(list 4874.2921 -413.2929) 
(list 4874.5089 -413.6173) 
(list 4874.585 -414) 
(list 4874.585 -411.8) 
(list 4874.585 -411.8) 
(list 4874.5089 -412.1827) 
(list 4874.2921 -412.5071) 
(list 4873.9677 -412.7239) 
(list 4873.585 -412.8) 
(list 4800.0615 -412.8) 
(list 4800.0615 -410.8) 
(list 4799.9385 -410.8) 
(list 4799.9385 -412.8) 
(list 4726.415 -412.8) 
(list 4726.0323 -412.7239) 
(list 4725.7079 -412.5071) 
(list 4725.4911 -412.1827) 
(list 4725.415 -411.8) 
(list 4725.415 -411.8) 
(list 4725.415 -414) 
(list 4725.4911 -413.6173) 
(list 4725.7079 -413.2929) 
(list 4726.0323 -413.0761) 
(list 4726.415 -413) 
(list 4726.415 -413) 
(list 4799.9385 -413) 
(list 4799.9385 -415)))
(apply 'command (append '("pline") coords '("c")))
(setq currobj (ssadd (entlast) currobj))
(command "._fillet" "radius" "0.3" "._fillet" "P" (entlast))
(command "_layer" "set" "holes" "")
(command "_circle" "4800,-412.9" "0.113")
(setq currobj (ssadd (entlast) currobj))
(command "_layer" "set" "nitride" "")
(command "_layer" "set" "text" "")
(command "_circle" "4799.2,-415" "0.075")
(command "_circle" "4799.2,-414.7" "0.075")
(command "_circle" "4799.2,-414.4" "0.075")
(command "_circle" "4798.9,-415" "0.075")
(command "_circle" "4798.9,-414.7" "0.075")
(command "_circle" "4798.9,-414.4" "0.075")
(command "_circle" "4798.6,-415" "0.075")
(command "_circle" "4798.6,-414.7" "0.075")
(command "_circle" "4798.6,-414.4" "0.075")
(command "_layer" "set" "nitride" "")
(command "_layer" "set" "prebias" "")
(command "_rectangle" "4725.415,-414" "4874.585,-411.8")
(setq currobj (ssadd (entlast) currobj))
(command "_rectangle" "4799.9385,-415" "4800.0615,-410.8")
(setq currobj (ssadd (entlast) currobj))
(command "_layer" "set" "nitride" "")
(setq coupler15 currobj)
(setq currobj nil)
(setq currobj (ssadd))
; DRAWING SINGLE NANOBEAM
(setq coords (list 
(list 4800.0615 -410.8) 
(list 4800.0615 -409.1417) 
(list 4800.0615 -407.4833) 
(list 4800.0615 -405.825) 
(list 4800.0615 -404.1667) 
(list 4800.0615 -402.5083) 
(list 4800.0615 -400.85) 
(list 4800.0615 -399.1917) 
(list 4800.0615 -397.5333) 
(list 4800.0616 -395.875) 
(list 4800.0616 -394.2167) 
(list 4800.0616 -392.5583) 
(list 4800.0616 -390.9) 
(list 4800.0617 -389.2417) 
(list 4800.0617 -387.5833) 
(list 4800.0617 -385.925) 
(list 4800.0618 -384.2667) 
(list 4800.0619 -382.6083) 
(list 4800.0619 -380.95) 
(list 4800.062 -379.2917) 
(list 4800.0621 -377.6333) 
(list 4800.0622 -375.975) 
(list 4800.0623 -374.3167) 
(list 4800.0624 -372.6583) 
(list 4800.0625 -371) 
(list 4800.0626 -369.3417) 
(list 4800.0628 -367.6833) 
(list 4800.0629 -366.025) 
(list 4800.0631 -364.3667) 
(list 4800.0632 -362.7083) 
(list 4800.0634 -361.05) 
(list 4800.0636 -359.3917) 
(list 4800.0638 -357.7333) 
(list 4800.0641 -356.075) 
(list 4800.0643 -354.4167) 
(list 4800.0646 -352.7583) 
(list 4800.0648 -351.1) 
(list 4800.0651 -349.4417) 
(list 4800.0654 -347.7833) 
(list 4800.0657 -346.125) 
(list 4800.0661 -344.4667) 
(list 4800.0664 -342.8083) 
(list 4800.0668 -341.15) 
(list 4800.0672 -339.4917) 
(list 4800.0676 -337.8333) 
(list 4800.068 -336.175) 
(list 4800.0685 -334.5167) 
(list 4800.0689 -332.8583) 
(list 4800.0694 -331.2) 
(list 4800.0699 -329.5417) 
(list 4800.0704 -327.8833) 
(list 4800.071 -326.225) 
(list 4800.0715 -324.5667) 
(list 4800.0721 -322.9083) 
(list 4800.0728 -321.25) 
(list 4800.0734 -319.5917) 
(list 4800.0741 -317.9333) 
(list 4800.0747 -316.275) 
(list 4800.0754 -314.6167) 
(list 4800.0762 -312.9583) 
(list 4800.0769 -311.3) 
(list 4800.0777 -309.6417) 
(list 4800.0785 -307.9833) 
(list 4800.0794 -306.325) 
(list 4800.0802 -304.6667) 
(list 4800.0811 -303.0083) 
(list 4800.082 -301.35) 
(list 4800.083 -299.6917) 
(list 4800.084 -298.0333) 
(list 4800.085 -296.375) 
(list 4800.086 -294.7167) 
(list 4800.0871 -293.0583) 
(list 4800.0882 -291.4) 
(list 4800.0893 -289.7417) 
(list 4800.0905 -288.0833) 
(list 4800.0917 -286.425) 
(list 4800.0929 -284.7667) 
(list 4800.0941 -283.1083) 
(list 4800.0954 -281.45) 
(list 4800.0967 -279.7917) 
(list 4800.0981 -278.1333) 
(list 4800.0995 -276.475) 
(list 4800.1009 -274.8167) 
(list 4800.1024 -273.1583) 
(list 4800.1039 -271.5) 
(list 4800.1054 -269.8417) 
(list 4800.107 -268.1833) 
(list 4800.1086 -266.525) 
(list 4800.1102 -264.8667) 
(list 4800.1119 -263.2083) 
(list 4800.1136 -261.55) 
(list 4800.1154 -259.8917) 
(list 4800.1172 -258.2333) 
(list 4800.119 -256.575) 
(list 4800.1209 -254.9167) 
(list 4800.1228 -253.2583) 
(list 4800.1247 -251.6) 
(list 4800.1267 -249.9417) 
(list 4800.1288 -248.2833) 
(list 4800.1308 -246.625) 
(list 4800.133 -244.9667) 
(list 4800.1351 -243.3083) 
(list 4800.1373 -241.65) 
(list 4800.1396 -239.9917) 
(list 4800.1419 -238.3333) 
(list 4800.1442 -236.675) 
(list 4800.1466 -235.0167) 
(list 4800.1491 -233.3583) 
(list 4800.1515 -231.7) 
(list 4800.1541 -230.0417) 
(list 4800.1566 -228.3833) 
(list 4800.1592 -226.725) 
(list 4800.1619 -225.0667) 
(list 4800.1646 -223.4083) 
(list 4800.1674 -221.75) 
(list 4800.1702 -220.0917) 
(list 4800.1731 -218.4333) 
(list 4800.176 -216.775) 
(list 4800.1789 -215.1167) 
(list 4800.1819 -213.4583) 
(list 4800.185 -211.8) 
(list 4799.815 -211.8) 
(list 4799.8181 -213.4583) 
(list 4799.8211 -215.1167) 
(list 4799.824 -216.775) 
(list 4799.8269 -218.4333) 
(list 4799.8298 -220.0917) 
(list 4799.8326 -221.75) 
(list 4799.8354 -223.4083) 
(list 4799.8381 -225.0667) 
(list 4799.8408 -226.725) 
(list 4799.8434 -228.3833) 
(list 4799.8459 -230.0417) 
(list 4799.8485 -231.7) 
(list 4799.8509 -233.3583) 
(list 4799.8534 -235.0167) 
(list 4799.8558 -236.675) 
(list 4799.8581 -238.3333) 
(list 4799.8604 -239.9917) 
(list 4799.8627 -241.65) 
(list 4799.8649 -243.3083) 
(list 4799.867 -244.9667) 
(list 4799.8692 -246.625) 
(list 4799.8712 -248.2833) 
(list 4799.8733 -249.9417) 
(list 4799.8753 -251.6) 
(list 4799.8772 -253.2583) 
(list 4799.8791 -254.9167) 
(list 4799.881 -256.575) 
(list 4799.8828 -258.2333) 
(list 4799.8846 -259.8917) 
(list 4799.8864 -261.55) 
(list 4799.8881 -263.2083) 
(list 4799.8898 -264.8667) 
(list 4799.8914 -266.525) 
(list 4799.893 -268.1833) 
(list 4799.8946 -269.8417) 
(list 4799.8961 -271.5) 
(list 4799.8976 -273.1583) 
(list 4799.8991 -274.8167) 
(list 4799.9005 -276.475) 
(list 4799.9019 -278.1333) 
(list 4799.9033 -279.7917) 
(list 4799.9046 -281.45) 
(list 4799.9059 -283.1083) 
(list 4799.9071 -284.7667) 
(list 4799.9083 -286.425) 
(list 4799.9095 -288.0833) 
(list 4799.9107 -289.7417) 
(list 4799.9118 -291.4) 
(list 4799.9129 -293.0583) 
(list 4799.914 -294.7167) 
(list 4799.915 -296.375) 
(list 4799.916 -298.0333) 
(list 4799.917 -299.6917) 
(list 4799.918 -301.35) 
(list 4799.9189 -303.0083) 
(list 4799.9198 -304.6667) 
(list 4799.9206 -306.325) 
(list 4799.9215 -307.9833) 
(list 4799.9223 -309.6417) 
(list 4799.9231 -311.3) 
(list 4799.9238 -312.9583) 
(list 4799.9246 -314.6167) 
(list 4799.9253 -316.275) 
(list 4799.9259 -317.9333) 
(list 4799.9266 -319.5917) 
(list 4799.9272 -321.25) 
(list 4799.9279 -322.9083) 
(list 4799.9285 -324.5667) 
(list 4799.929 -326.225) 
(list 4799.9296 -327.8833) 
(list 4799.9301 -329.5417) 
(list 4799.9306 -331.2) 
(list 4799.9311 -332.8583) 
(list 4799.9315 -334.5167) 
(list 4799.932 -336.175) 
(list 4799.9324 -337.8333) 
(list 4799.9328 -339.4917) 
(list 4799.9332 -341.15) 
(list 4799.9336 -342.8083) 
(list 4799.9339 -344.4667) 
(list 4799.9343 -346.125) 
(list 4799.9346 -347.7833) 
(list 4799.9349 -349.4417) 
(list 4799.9352 -351.1) 
(list 4799.9354 -352.7583) 
(list 4799.9357 -354.4167) 
(list 4799.9359 -356.075) 
(list 4799.9362 -357.7333) 
(list 4799.9364 -359.3917) 
(list 4799.9366 -361.05) 
(list 4799.9368 -362.7083) 
(list 4799.9369 -364.3667) 
(list 4799.9371 -366.025) 
(list 4799.9372 -367.6833) 
(list 4799.9374 -369.3417) 
(list 4799.9375 -371) 
(list 4799.9376 -372.6583) 
(list 4799.9377 -374.3167) 
(list 4799.9378 -375.975) 
(list 4799.9379 -377.6333) 
(list 4799.938 -379.2917) 
(list 4799.9381 -380.95) 
(list 4799.9381 -382.6083) 
(list 4799.9382 -384.2667) 
(list 4799.9383 -385.925) 
(list 4799.9383 -387.5833) 
(list 4799.9383 -389.2417) 
(list 4799.9384 -390.9) 
(list 4799.9384 -392.5583) 
(list 4799.9384 -394.2167) 
(list 4799.9384 -395.875) 
(list 4799.9385 -397.5333) 
(list 4799.9385 -399.1917) 
(list 4799.9385 -400.85) 
(list 4799.9385 -402.5083) 
(list 4799.9385 -404.1667) 
(list 4799.9385 -405.825) 
(list 4799.9385 -407.4833) 
(list 4799.9385 -409.1417) 
(list 4799.9385 -410.8)))
(apply 'command (append '("pline") coords '("c")))
(setq currobj (ssadd (entlast) currobj))
(command "_layer" "set" "prebias" "")
(command "_rectangle" "4799.815,-410.8" "4800.185,-211.8")
(setq currobj (ssadd (entlast) currobj))
(command "_layer" "set" "nitride" "")
(setq singlenanobeam15 currobj)
(setq currobj nil)
(setq currobj (ssadd))
; DRAWING NODE ARRAY
(setq coords (list 
(list 4800.185 -211.8) 
(list 4800.5625 -201.8) 
(list 4800.5625 -201.8) 
(list 4800.5625 -200.8) 
(list 4874.585 -212.6864) 
(list 4874.585 -207.7434) 
(list 4800.5625 -197.357) 
(list 4800.5625 -196.357) 
(list 4800.5625 -196.357) 
(list 4800.2625 -186.357) 
(list 4799.7375 -186.357) 
(list 4799.4375 -196.357) 
(list 4799.4375 -196.357) 
(list 4799.4375 -197.357) 
(list 4725.415 -207.7434) 
(list 4725.415 -212.6864) 
(list 4799.4375 -200.8) 
(list 4799.4375 -201.8) 
(list 4799.4375 -201.8) 
(list 4799.815 -211.8)))
(apply 'command (append '("pline") coords '("c")))
(setq currobj (ssadd (entlast) currobj))
(command "_layer" "set" "prebias" "")
(setq coords (list 
(list 4799.4375 -212.6864) 
(list 4799.4375 -200.8) 
(list 4725.415 -212.6864) 
(list 4725.415 -207.7434) 
(list 4799.4375 -197.357) 
(list 4799.4375 -186.357) 
(list 4800.5625 -186.357) 
(list 4800.5625 -197.357) 
(list 4874.585 -207.7434) 
(list 4874.585 -212.6864) 
(list 4800.5625 -200.8) 
(list 4800.5625 -212.6864)))
(apply 'command (append '("pline") coords '("c")))
(setq currobj (ssadd (entlast) currobj))
(command "_layer" "set" "nitride" "")
(command "_layer" "set" "fda1" "")
(setq coords (list 
(list 4800.5625 -200.657) 
(list 4874.585 -212.5434) 
(list 4874.585 -212.3664) 
(list 4800.5625 -200.58)))
(apply 'command (append '("pline") coords '("c")))
(setq currobj (ssadd (entlast) currobj))
(setq coords (list 
(list 4800.5625 -200.437) 
(list 4874.585 -212.2234) 
(list 4874.585 -212.0464) 
(list 4800.5625 -200.36)))
(apply 'command (append '("pline") coords '("c")))
(setq currobj (ssadd (entlast) currobj))
(setq coords (list 
(list 4800.5625 -200.217) 
(list 4874.585 -211.9034) 
(list 4874.585 -211.7264) 
(list 4800.5625 -200.14)))
(apply 'command (append '("pline") coords '("c")))
(setq currobj (ssadd (entlast) currobj))
(setq coords (list 
(list 4800.5625 -199.997) 
(list 4874.585 -211.5834) 
(list 4874.585 -211.4064) 
(list 4800.5625 -199.92)))
(apply 'command (append '("pline") coords '("c")))
(setq currobj (ssadd (entlast) currobj))
(setq coords (list 
(list 4800.5625 -199.777) 
(list 4874.585 -211.2634) 
(list 4874.585 -211.0864) 
(list 4800.5625 -199.7)))
(apply 'command (append '("pline") coords '("c")))
(setq currobj (ssadd (entlast) currobj))
(setq coords (list 
(list 4800.5625 -199.557) 
(list 4874.585 -210.9434) 
(list 4874.585 -210.7664) 
(list 4800.5625 -199.48)))
(apply 'command (append '("pline") coords '("c")))
(setq currobj (ssadd (entlast) currobj))
(setq coords (list 
(list 4800.5625 -199.337) 
(list 4874.585 -210.6234) 
(list 4874.585 -210.4464) 
(list 4800.5625 -199.26)))
(apply 'command (append '("pline") coords '("c")))
(setq currobj (ssadd (entlast) currobj))
(setq coords (list 
(list 4800.5625 -199.117) 
(list 4874.585 -210.3034) 
(list 4874.585 -210.1264) 
(list 4800.5625 -199.04)))
(apply 'command (append '("pline") coords '("c")))
(setq currobj (ssadd (entlast) currobj))
(setq coords (list 
(list 4800.5625 -198.897) 
(list 4874.585 -209.9834) 
(list 4874.585 -209.8064) 
(list 4800.5625 -198.82)))
(apply 'command (append '("pline") coords '("c")))
(setq currobj (ssadd (entlast) currobj))
(setq coords (list 
(list 4800.5625 -198.677) 
(list 4874.585 -209.6634) 
(list 4874.585 -209.4864) 
(list 4800.5625 -198.6)))
(apply 'command (append '("pline") coords '("c")))
(setq currobj (ssadd (entlast) currobj))
(setq coords (list 
(list 4800.5625 -198.457) 
(list 4874.585 -209.3434) 
(list 4874.585 -209.1664) 
(list 4800.5625 -198.38)))
(apply 'command (append '("pline") coords '("c")))
(setq currobj (ssadd (entlast) currobj))
(setq coords (list 
(list 4800.5625 -198.237) 
(list 4874.585 -209.0234) 
(list 4874.585 -208.8464) 
(list 4800.5625 -198.16)))
(apply 'command (append '("pline") coords '("c")))
(setq currobj (ssadd (entlast) currobj))
(setq coords (list 
(list 4800.5625 -198.017) 
(list 4874.585 -208.7034) 
(list 4874.585 -208.5264) 
(list 4800.5625 -197.94)))
(apply 'command (append '("pline") coords '("c")))
(setq currobj (ssadd (entlast) currobj))
(setq coords (list 
(list 4800.5625 -197.797) 
(list 4874.585 -208.3834) 
(list 4874.585 -208.2064) 
(list 4800.5625 -197.72)))
(apply 'command (append '("pline") coords '("c")))
(setq currobj (ssadd (entlast) currobj))
(setq coords (list 
(list 4800.5625 -197.577) 
(list 4874.585 -208.0634) 
(list 4874.585 -207.8864) 
(list 4800.5625 -197.5)))
(apply 'command (append '("pline") coords '("c")))
(setq currobj (ssadd (entlast) currobj))
(setq coords (list 
(list 4799.4375 -197.5) 
(list 4725.415 -207.8864) 
(list 4725.415 -208.0634) 
(list 4799.4375 -197.577)))
(apply 'command (append '("pline") coords '("c")))
(setq currobj (ssadd (entlast) currobj))
(setq coords (list 
(list 4799.4375 -197.72) 
(list 4725.415 -208.2064) 
(list 4725.415 -208.3834) 
(list 4799.4375 -197.797)))
(apply 'command (append '("pline") coords '("c")))
(setq currobj (ssadd (entlast) currobj))
(setq coords (list 
(list 4799.4375 -197.94) 
(list 4725.415 -208.5264) 
(list 4725.415 -208.7034) 
(list 4799.4375 -198.017)))
(apply 'command (append '("pline") coords '("c")))
(setq currobj (ssadd (entlast) currobj))
(setq coords (list 
(list 4799.4375 -198.16) 
(list 4725.415 -208.8464) 
(list 4725.415 -209.0234) 
(list 4799.4375 -198.237)))
(apply 'command (append '("pline") coords '("c")))
(setq currobj (ssadd (entlast) currobj))
(setq coords (list 
(list 4799.4375 -198.38) 
(list 4725.415 -209.1664) 
(list 4725.415 -209.3434) 
(list 4799.4375 -198.457)))
(apply 'command (append '("pline") coords '("c")))
(setq currobj (ssadd (entlast) currobj))
(setq coords (list 
(list 4799.4375 -198.6) 
(list 4725.415 -209.4864) 
(list 4725.415 -209.6634) 
(list 4799.4375 -198.677)))
(apply 'command (append '("pline") coords '("c")))
(setq currobj (ssadd (entlast) currobj))
(setq coords (list 
(list 4799.4375 -198.82) 
(list 4725.415 -209.8064) 
(list 4725.415 -209.9834) 
(list 4799.4375 -198.897)))
(apply 'command (append '("pline") coords '("c")))
(setq currobj (ssadd (entlast) currobj))
(setq coords (list 
(list 4799.4375 -199.04) 
(list 4725.415 -210.1264) 
(list 4725.415 -210.3034) 
(list 4799.4375 -199.117)))
(apply 'command (append '("pline") coords '("c")))
(setq currobj (ssadd (entlast) currobj))
(setq coords (list 
(list 4799.4375 -199.26) 
(list 4725.415 -210.4464) 
(list 4725.415 -210.6234) 
(list 4799.4375 -199.337)))
(apply 'command (append '("pline") coords '("c")))
(setq currobj (ssadd (entlast) currobj))
(setq coords (list 
(list 4799.4375 -199.48) 
(list 4725.415 -210.7664) 
(list 4725.415 -210.9434) 
(list 4799.4375 -199.557)))
(apply 'command (append '("pline") coords '("c")))
(setq currobj (ssadd (entlast) currobj))
(setq coords (list 
(list 4799.4375 -199.7) 
(list 4725.415 -211.0864) 
(list 4725.415 -211.2634) 
(list 4799.4375 -199.777)))
(apply 'command (append '("pline") coords '("c")))
(setq currobj (ssadd (entlast) currobj))
(setq coords (list 
(list 4799.4375 -199.92) 
(list 4725.415 -211.4064) 
(list 4725.415 -211.5834) 
(list 4799.4375 -199.997)))
(apply 'command (append '("pline") coords '("c")))
(setq currobj (ssadd (entlast) currobj))
(setq coords (list 
(list 4799.4375 -200.14) 
(list 4725.415 -211.7264) 
(list 4725.415 -211.9034) 
(list 4799.4375 -200.217)))
(apply 'command (append '("pline") coords '("c")))
(setq currobj (ssadd (entlast) currobj))
(setq coords (list 
(list 4799.4375 -200.36) 
(list 4725.415 -212.0464) 
(list 4725.415 -212.2234) 
(list 4799.4375 -200.437)))
(apply 'command (append '("pline") coords '("c")))
(setq currobj (ssadd (entlast) currobj))
(setq coords (list 
(list 4799.4375 -200.58) 
(list 4725.415 -212.3664) 
(list 4725.415 -212.5434) 
(list 4799.4375 -200.657)))
(apply 'command (append '("pline") coords '("c")))
(setq currobj (ssadd (entlast) currobj))
(command "_layer" "set" "nitride" "")
(command "_layer" "set" "text" "")
(command "_circle" "4798.985,-211.8" "0.075")
(command "_circle" "4798.985,-211.5" "0.075")
(command "_circle" "4798.985,-211.2" "0.075")
(command "_circle" "4798.985,-210.9" "0.075")
(command "_circle" "4798.985,-210.6" "0.075")
(command "_circle" "4798.685,-211.8" "0.075")
(command "_circle" "4798.685,-211.5" "0.075")
(command "_circle" "4798.685,-211.2" "0.075")
(command "_circle" "4798.685,-210.9" "0.075")
(command "_circle" "4798.685,-210.6" "0.075")
(command "_circle" "4798.385,-211.8" "0.075")
(command "_circle" "4798.385,-211.5" "0.075")
(command "_circle" "4798.385,-211.2" "0.075")
(command "_circle" "4798.385,-210.9" "0.075")
(command "_circle" "4798.385,-210.6" "0.075")
(command "_circle" "4798.085,-211.8" "0.075")
(command "_circle" "4798.085,-211.5" "0.075")
(command "_circle" "4798.085,-211.2" "0.075")
(command "_circle" "4798.085,-210.9" "0.075")
(command "_circle" "4798.085,-210.6" "0.075")
(command "_circle" "4797.785,-211.8" "0.075")
(command "_circle" "4797.785,-211.5" "0.075")
(command "_circle" "4797.785,-211.2" "0.075")
(command "_circle" "4797.785,-210.9" "0.075")
(command "_circle" "4797.785,-210.6" "0.075")
(command "_layer" "set" "nitride" "")
(setq anglednodearray15 currobj)
(setq currobj nil)
(setq currobj (ssadd))
; DRAWING COOLED SINGLE NANOBEAM
(setq coords (list 
(list 4800.2625 -186.357) 
(list 4800.2625 -181.357) 
(list 4799.7375 -181.357) 
(list 4799.7375 -186.357)))
(apply 'command (append '("pline") coords '("c")))
(setq currobj (ssadd (entlast) currobj))
(command "_layer" "set" "prebias" "")
(command "_rectangle" "4799.7375,-186.357" "4800.2625,-181.357")
(setq currobj (ssadd (entlast) currobj))
(command "_layer" "set" "nitride" "")
(setq coords (list 
(list 4800.2625 -181.357) 
(list 4800.5625 -171.357) 
(list 4800.5625 -171.357) 
(list 4800.5625 -170.357) 
(list 4874.585 -171.107) 
(list 4874.585 -166.164) 
(list 4800.5625 -166.914) 
(list 4800.5625 -165.914) 
(list 4800.5625 -165.914) 
(list 4800.2625 -155.914) 
(list 4799.7375 -155.914) 
(list 4799.4375 -165.914) 
(list 4799.4375 -165.914) 
(list 4799.4375 -166.914) 
(list 4725.415 -166.164) 
(list 4725.415 -171.107) 
(list 4799.4375 -170.357) 
(list 4799.4375 -171.357) 
(list 4799.4375 -171.357) 
(list 4799.7375 -181.357)))
(apply 'command (append '("pline") coords '("c")))
(setq currobj (ssadd (entlast) currobj))
(command "_layer" "set" "prebias" "")
(setq coords (list 
(list 4799.4375 -181.357) 
(list 4799.4375 -170.357) 
(list 4725.415 -171.107) 
(list 4725.415 -166.164) 
(list 4799.4375 -166.914) 
(list 4799.4375 -155.914) 
(list 4800.5625 -155.914) 
(list 4800.5625 -166.914) 
(list 4874.585 -166.164) 
(list 4874.585 -171.107) 
(list 4800.5625 -170.357) 
(list 4800.5625 -181.357)))
(apply 'command (append '("pline") coords '("c")))
(setq currobj (ssadd (entlast) currobj))
(command "_layer" "set" "nitride" "")
(command "_layer" "set" "fda1" "")
(setq coords (list 
(list 4800.5625 -170.214) 
(list 4874.585 -170.964) 
(list 4874.585 -170.787) 
(list 4800.5625 -170.137)))
(apply 'command (append '("pline") coords '("c")))
(setq currobj (ssadd (entlast) currobj))
(setq coords (list 
(list 4800.5625 -169.994) 
(list 4874.585 -170.644) 
(list 4874.585 -170.467) 
(list 4800.5625 -169.917)))
(apply 'command (append '("pline") coords '("c")))
(setq currobj (ssadd (entlast) currobj))
(setq coords (list 
(list 4800.5625 -169.774) 
(list 4874.585 -170.324) 
(list 4874.585 -170.147) 
(list 4800.5625 -169.697)))
(apply 'command (append '("pline") coords '("c")))
(setq currobj (ssadd (entlast) currobj))
(setq coords (list 
(list 4800.5625 -169.554) 
(list 4874.585 -170.004) 
(list 4874.585 -169.827) 
(list 4800.5625 -169.477)))
(apply 'command (append '("pline") coords '("c")))
(setq currobj (ssadd (entlast) currobj))
(setq coords (list 
(list 4800.5625 -169.334) 
(list 4874.585 -169.684) 
(list 4874.585 -169.507) 
(list 4800.5625 -169.257)))
(apply 'command (append '("pline") coords '("c")))
(setq currobj (ssadd (entlast) currobj))
(setq coords (list 
(list 4800.5625 -169.114) 
(list 4874.585 -169.364) 
(list 4874.585 -169.187) 
(list 4800.5625 -169.037)))
(apply 'command (append '("pline") coords '("c")))
(setq currobj (ssadd (entlast) currobj))
(setq coords (list 
(list 4800.5625 -168.894) 
(list 4874.585 -169.044) 
(list 4874.585 -168.867) 
(list 4800.5625 -168.817)))
(apply 'command (append '("pline") coords '("c")))
(setq currobj (ssadd (entlast) currobj))
(setq coords (list 
(list 4800.5625 -168.674) 
(list 4874.585 -168.724) 
(list 4874.585 -168.547) 
(list 4800.5625 -168.597)))
(apply 'command (append '("pline") coords '("c")))
(setq currobj (ssadd (entlast) currobj))
(setq coords (list 
(list 4800.5625 -168.454) 
(list 4874.585 -168.404) 
(list 4874.585 -168.227) 
(list 4800.5625 -168.377)))
(apply 'command (append '("pline") coords '("c")))
(setq currobj (ssadd (entlast) currobj))
(setq coords (list 
(list 4800.5625 -168.234) 
(list 4874.585 -168.084) 
(list 4874.585 -167.907) 
(list 4800.5625 -168.157)))
(apply 'command (append '("pline") coords '("c")))
(setq currobj (ssadd (entlast) currobj))
(setq coords (list 
(list 4800.5625 -168.014) 
(list 4874.585 -167.764) 
(list 4874.585 -167.587) 
(list 4800.5625 -167.937)))
(apply 'command (append '("pline") coords '("c")))
(setq currobj (ssadd (entlast) currobj))
(setq coords (list 
(list 4800.5625 -167.794) 
(list 4874.585 -167.444) 
(list 4874.585 -167.267) 
(list 4800.5625 -167.717)))
(apply 'command (append '("pline") coords '("c")))
(setq currobj (ssadd (entlast) currobj))
(setq coords (list 
(list 4800.5625 -167.574) 
(list 4874.585 -167.124) 
(list 4874.585 -166.947) 
(list 4800.5625 -167.497)))
(apply 'command (append '("pline") coords '("c")))
(setq currobj (ssadd (entlast) currobj))
(setq coords (list 
(list 4800.5625 -167.354) 
(list 4874.585 -166.804) 
(list 4874.585 -166.627) 
(list 4800.5625 -167.277)))
(apply 'command (append '("pline") coords '("c")))
(setq currobj (ssadd (entlast) currobj))
(setq coords (list 
(list 4800.5625 -167.134) 
(list 4874.585 -166.484) 
(list 4874.585 -166.307) 
(list 4800.5625 -167.057)))
(apply 'command (append '("pline") coords '("c")))
(setq currobj (ssadd (entlast) currobj))
(setq coords (list 
(list 4799.4375 -167.057) 
(list 4725.415 -166.307) 
(list 4725.415 -166.484) 
(list 4799.4375 -167.134)))
(apply 'command (append '("pline") coords '("c")))
(setq currobj (ssadd (entlast) currobj))
(setq coords (list 
(list 4799.4375 -167.277) 
(list 4725.415 -166.627) 
(list 4725.415 -166.804) 
(list 4799.4375 -167.354)))
(apply 'command (append '("pline") coords '("c")))
(setq currobj (ssadd (entlast) currobj))
(setq coords (list 
(list 4799.4375 -167.497) 
(list 4725.415 -166.947) 
(list 4725.415 -167.124) 
(list 4799.4375 -167.574)))
(apply 'command (append '("pline") coords '("c")))
(setq currobj (ssadd (entlast) currobj))
(setq coords (list 
(list 4799.4375 -167.717) 
(list 4725.415 -167.267) 
(list 4725.415 -167.444) 
(list 4799.4375 -167.794)))
(apply 'command (append '("pline") coords '("c")))
(setq currobj (ssadd (entlast) currobj))
(setq coords (list 
(list 4799.4375 -167.937) 
(list 4725.415 -167.587) 
(list 4725.415 -167.764) 
(list 4799.4375 -168.014)))
(apply 'command (append '("pline") coords '("c")))
(setq currobj (ssadd (entlast) currobj))
(setq coords (list 
(list 4799.4375 -168.157) 
(list 4725.415 -167.907) 
(list 4725.415 -168.084) 
(list 4799.4375 -168.234)))
(apply 'command (append '("pline") coords '("c")))
(setq currobj (ssadd (entlast) currobj))
(setq coords (list 
(list 4799.4375 -168.377) 
(list 4725.415 -168.227) 
(list 4725.415 -168.404) 
(list 4799.4375 -168.454)))
(apply 'command (append '("pline") coords '("c")))
(setq currobj (ssadd (entlast) currobj))
(setq coords (list 
(list 4799.4375 -168.597) 
(list 4725.415 -168.547) 
(list 4725.415 -168.724) 
(list 4799.4375 -168.674)))
(apply 'command (append '("pline") coords '("c")))
(setq currobj (ssadd (entlast) currobj))
(setq coords (list 
(list 4799.4375 -168.817) 
(list 4725.415 -168.867) 
(list 4725.415 -169.044) 
(list 4799.4375 -168.894)))
(apply 'command (append '("pline") coords '("c")))
(setq currobj (ssadd (entlast) currobj))
(setq coords (list 
(list 4799.4375 -169.037) 
(list 4725.415 -169.187) 
(list 4725.415 -169.364) 
(list 4799.4375 -169.114)))
(apply 'command (append '("pline") coords '("c")))
(setq currobj (ssadd (entlast) currobj))
(setq coords (list 
(list 4799.4375 -169.257) 
(list 4725.415 -169.507) 
(list 4725.415 -169.684) 
(list 4799.4375 -169.334)))
(apply 'command (append '("pline") coords '("c")))
(setq currobj (ssadd (entlast) currobj))
(setq coords (list 
(list 4799.4375 -169.477) 
(list 4725.415 -169.827) 
(list 4725.415 -170.004) 
(list 4799.4375 -169.554)))
(apply 'command (append '("pline") coords '("c")))
(setq currobj (ssadd (entlast) currobj))
(setq coords (list 
(list 4799.4375 -169.697) 
(list 4725.415 -170.147) 
(list 4725.415 -170.324) 
(list 4799.4375 -169.774)))
(apply 'command (append '("pline") coords '("c")))
(setq currobj (ssadd (entlast) currobj))
(setq coords (list 
(list 4799.4375 -169.917) 
(list 4725.415 -170.467) 
(list 4725.415 -170.644) 
(list 4799.4375 -169.994)))
(apply 'command (append '("pline") coords '("c")))
(setq currobj (ssadd (entlast) currobj))
(setq coords (list 
(list 4799.4375 -170.137) 
(list 4725.415 -170.787) 
(list 4725.415 -170.964) 
(list 4799.4375 -170.214)))
(apply 'command (append '("pline") coords '("c")))
(setq currobj (ssadd (entlast) currobj))
(command "_layer" "set" "nitride" "")
(command "_layer" "set" "text" "")
(command "_circle" "4799.0625,-181.357" "0.075")
(command "_circle" "4799.0625,-181.057" "0.075")
(command "_circle" "4799.0625,-180.757" "0.075")
(command "_circle" "4799.0625,-180.457" "0.075")
(command "_circle" "4799.0625,-180.157" "0.075")
(command "_circle" "4798.7625,-181.357" "0.075")
(command "_circle" "4798.7625,-181.057" "0.075")
(command "_circle" "4798.7625,-180.757" "0.075")
(command "_circle" "4798.7625,-180.457" "0.075")
(command "_circle" "4798.7625,-180.157" "0.075")
(command "_circle" "4798.4625,-181.357" "0.075")
(command "_circle" "4798.4625,-181.057" "0.075")
(command "_circle" "4798.4625,-180.757" "0.075")
(command "_circle" "4798.4625,-180.457" "0.075")
(command "_circle" "4798.4625,-180.157" "0.075")
(command "_circle" "4798.1625,-181.357" "0.075")
(command "_circle" "4798.1625,-181.057" "0.075")
(command "_circle" "4798.1625,-180.757" "0.075")
(command "_circle" "4798.1625,-180.457" "0.075")
(command "_circle" "4798.1625,-180.157" "0.075")
(command "_circle" "4797.8625,-181.357" "0.075")
(command "_circle" "4797.8625,-181.057" "0.075")
(command "_circle" "4797.8625,-180.757" "0.075")
(command "_circle" "4797.8625,-180.457" "0.075")
(command "_circle" "4797.8625,-180.157" "0.075")
(command "_layer" "set" "nitride" "")
(setq coords (list 
(list 4800.2625 -155.914) 
(list 4800.2625 -40.2693) 
(list 4799.7375 -40.2693) 
(list 4799.7375 -155.914)))
(apply 'command (append '("pline") coords '("c")))
(setq currobj (ssadd (entlast) currobj))
(command "_layer" "set" "prebias" "")
(command "_rectangle" "4799.7375,-155.914" "4800.2625,-40.2693")
(setq currobj (ssadd (entlast) currobj))
(command "_layer" "set" "nitride" "")
(setq coords (list 
(list 4800.2625 -40.2693) 
(list 4800.5625 -30.2693) 
(list 4800.5625 -30.2693) 
(list 4800.5625 -29.2693) 
(list 4874.585 -30.0193) 
(list 4874.585 -25.0763) 
(list 4800.5625 -25.8263) 
(list 4800.5625 -24.8263) 
(list 4800.5625 -24.8263) 
(list 4800.2625 -14.8263) 
(list 4799.7375 -14.8263) 
(list 4799.4375 -24.8263) 
(list 4799.4375 -24.8263) 
(list 4799.4375 -25.8263) 
(list 4725.415 -25.0763) 
(list 4725.415 -30.0193) 
(list 4799.4375 -29.2693) 
(list 4799.4375 -30.2693) 
(list 4799.4375 -30.2693) 
(list 4799.7375 -40.2693)))
(apply 'command (append '("pline") coords '("c")))
(setq currobj (ssadd (entlast) currobj))
(command "_layer" "set" "prebias" "")
(setq coords (list 
(list 4799.4375 -40.2693) 
(list 4799.4375 -29.2693) 
(list 4725.415 -30.0193) 
(list 4725.415 -25.0763) 
(list 4799.4375 -25.8263) 
(list 4799.4375 -14.8263) 
(list 4800.5625 -14.8263) 
(list 4800.5625 -25.8263) 
(list 4874.585 -25.0763) 
(list 4874.585 -30.0193) 
(list 4800.5625 -29.2693) 
(list 4800.5625 -40.2693)))
(apply 'command (append '("pline") coords '("c")))
(setq currobj (ssadd (entlast) currobj))
(command "_layer" "set" "nitride" "")
(command "_layer" "set" "fda1" "")
(setq coords (list 
(list 4800.5625 -29.1263) 
(list 4874.585 -29.8763) 
(list 4874.585 -29.6993) 
(list 4800.5625 -29.0493)))
(apply 'command (append '("pline") coords '("c")))
(setq currobj (ssadd (entlast) currobj))
(setq coords (list 
(list 4800.5625 -28.9063) 
(list 4874.585 -29.5563) 
(list 4874.585 -29.3793) 
(list 4800.5625 -28.8293)))
(apply 'command (append '("pline") coords '("c")))
(setq currobj (ssadd (entlast) currobj))
(setq coords (list 
(list 4800.5625 -28.6863) 
(list 4874.585 -29.2363) 
(list 4874.585 -29.0593) 
(list 4800.5625 -28.6093)))
(apply 'command (append '("pline") coords '("c")))
(setq currobj (ssadd (entlast) currobj))
(setq coords (list 
(list 4800.5625 -28.4663) 
(list 4874.585 -28.9163) 
(list 4874.585 -28.7393) 
(list 4800.5625 -28.3893)))
(apply 'command (append '("pline") coords '("c")))
(setq currobj (ssadd (entlast) currobj))
(setq coords (list 
(list 4800.5625 -28.2463) 
(list 4874.585 -28.5963) 
(list 4874.585 -28.4193) 
(list 4800.5625 -28.1693)))
(apply 'command (append '("pline") coords '("c")))
(setq currobj (ssadd (entlast) currobj))
(setq coords (list 
(list 4800.5625 -28.0263) 
(list 4874.585 -28.2763) 
(list 4874.585 -28.0993) 
(list 4800.5625 -27.9493)))
(apply 'command (append '("pline") coords '("c")))
(setq currobj (ssadd (entlast) currobj))
(setq coords (list 
(list 4800.5625 -27.8063) 
(list 4874.585 -27.9563) 
(list 4874.585 -27.7793) 
(list 4800.5625 -27.7293)))
(apply 'command (append '("pline") coords '("c")))
(setq currobj (ssadd (entlast) currobj))
(setq coords (list 
(list 4800.5625 -27.5863) 
(list 4874.585 -27.6363) 
(list 4874.585 -27.4593) 
(list 4800.5625 -27.5093)))
(apply 'command (append '("pline") coords '("c")))
(setq currobj (ssadd (entlast) currobj))
(setq coords (list 
(list 4800.5625 -27.3663) 
(list 4874.585 -27.3163) 
(list 4874.585 -27.1393) 
(list 4800.5625 -27.2893)))
(apply 'command (append '("pline") coords '("c")))
(setq currobj (ssadd (entlast) currobj))
(setq coords (list 
(list 4800.5625 -27.1463) 
(list 4874.585 -26.9963) 
(list 4874.585 -26.8193) 
(list 4800.5625 -27.0693)))
(apply 'command (append '("pline") coords '("c")))
(setq currobj (ssadd (entlast) currobj))
(setq coords (list 
(list 4800.5625 -26.9263) 
(list 4874.585 -26.6763) 
(list 4874.585 -26.4993) 
(list 4800.5625 -26.8493)))
(apply 'command (append '("pline") coords '("c")))
(setq currobj (ssadd (entlast) currobj))
(setq coords (list 
(list 4800.5625 -26.7063) 
(list 4874.585 -26.3563) 
(list 4874.585 -26.1793) 
(list 4800.5625 -26.6293)))
(apply 'command (append '("pline") coords '("c")))
(setq currobj (ssadd (entlast) currobj))
(setq coords (list 
(list 4800.5625 -26.4863) 
(list 4874.585 -26.0363) 
(list 4874.585 -25.8593) 
(list 4800.5625 -26.4093)))
(apply 'command (append '("pline") coords '("c")))
(setq currobj (ssadd (entlast) currobj))
(setq coords (list 
(list 4800.5625 -26.2663) 
(list 4874.585 -25.7163) 
(list 4874.585 -25.5393) 
(list 4800.5625 -26.1893)))
(apply 'command (append '("pline") coords '("c")))
(setq currobj (ssadd (entlast) currobj))
(setq coords (list 
(list 4800.5625 -26.0463) 
(list 4874.585 -25.3963) 
(list 4874.585 -25.2193) 
(list 4800.5625 -25.9693)))
(apply 'command (append '("pline") coords '("c")))
(setq currobj (ssadd (entlast) currobj))
(setq coords (list 
(list 4799.4375 -25.9693) 
(list 4725.415 -25.2193) 
(list 4725.415 -25.3963) 
(list 4799.4375 -26.0463)))
(apply 'command (append '("pline") coords '("c")))
(setq currobj (ssadd (entlast) currobj))
(setq coords (list 
(list 4799.4375 -26.1893) 
(list 4725.415 -25.5393) 
(list 4725.415 -25.7163) 
(list 4799.4375 -26.2663)))
(apply 'command (append '("pline") coords '("c")))
(setq currobj (ssadd (entlast) currobj))
(setq coords (list 
(list 4799.4375 -26.4093) 
(list 4725.415 -25.8593) 
(list 4725.415 -26.0363) 
(list 4799.4375 -26.4863)))
(apply 'command (append '("pline") coords '("c")))
(setq currobj (ssadd (entlast) currobj))
(setq coords (list 
(list 4799.4375 -26.6293) 
(list 4725.415 -26.1793) 
(list 4725.415 -26.3563) 
(list 4799.4375 -26.7063)))
(apply 'command (append '("pline") coords '("c")))
(setq currobj (ssadd (entlast) currobj))
(setq coords (list 
(list 4799.4375 -26.8493) 
(list 4725.415 -26.4993) 
(list 4725.415 -26.6763) 
(list 4799.4375 -26.9263)))
(apply 'command (append '("pline") coords '("c")))
(setq currobj (ssadd (entlast) currobj))
(setq coords (list 
(list 4799.4375 -27.0693) 
(list 4725.415 -26.8193) 
(list 4725.415 -26.9963) 
(list 4799.4375 -27.1463)))
(apply 'command (append '("pline") coords '("c")))
(setq currobj (ssadd (entlast) currobj))
(setq coords (list 
(list 4799.4375 -27.2893) 
(list 4725.415 -27.1393) 
(list 4725.415 -27.3163) 
(list 4799.4375 -27.3663)))
(apply 'command (append '("pline") coords '("c")))
(setq currobj (ssadd (entlast) currobj))
(setq coords (list 
(list 4799.4375 -27.5093) 
(list 4725.415 -27.4593) 
(list 4725.415 -27.6363) 
(list 4799.4375 -27.5863)))
(apply 'command (append '("pline") coords '("c")))
(setq currobj (ssadd (entlast) currobj))
(setq coords (list 
(list 4799.4375 -27.7293) 
(list 4725.415 -27.7793) 
(list 4725.415 -27.9563) 
(list 4799.4375 -27.8063)))
(apply 'command (append '("pline") coords '("c")))
(setq currobj (ssadd (entlast) currobj))
(setq coords (list 
(list 4799.4375 -27.9493) 
(list 4725.415 -28.0993) 
(list 4725.415 -28.2763) 
(list 4799.4375 -28.0263)))
(apply 'command (append '("pline") coords '("c")))
(setq currobj (ssadd (entlast) currobj))
(setq coords (list 
(list 4799.4375 -28.1693) 
(list 4725.415 -28.4193) 
(list 4725.415 -28.5963) 
(list 4799.4375 -28.2463)))
(apply 'command (append '("pline") coords '("c")))
(setq currobj (ssadd (entlast) currobj))
(setq coords (list 
(list 4799.4375 -28.3893) 
(list 4725.415 -28.7393) 
(list 4725.415 -28.9163) 
(list 4799.4375 -28.4663)))
(apply 'command (append '("pline") coords '("c")))
(setq currobj (ssadd (entlast) currobj))
(setq coords (list 
(list 4799.4375 -28.6093) 
(list 4725.415 -29.0593) 
(list 4725.415 -29.2363) 
(list 4799.4375 -28.6863)))
(apply 'command (append '("pline") coords '("c")))
(setq currobj (ssadd (entlast) currobj))
(setq coords (list 
(list 4799.4375 -28.8293) 
(list 4725.415 -29.3793) 
(list 4725.415 -29.5563) 
(list 4799.4375 -28.9063)))
(apply 'command (append '("pline") coords '("c")))
(setq currobj (ssadd (entlast) currobj))
(setq coords (list 
(list 4799.4375 -29.0493) 
(list 4725.415 -29.6993) 
(list 4725.415 -29.8763) 
(list 4799.4375 -29.1263)))
(apply 'command (append '("pline") coords '("c")))
(setq currobj (ssadd (entlast) currobj))
(command "_layer" "set" "nitride" "")
(command "_layer" "set" "text" "")
(command "_circle" "4799.0625,-40.2693" "0.075")
(command "_circle" "4799.0625,-39.9693" "0.075")
(command "_circle" "4799.0625,-39.6693" "0.075")
(command "_circle" "4799.0625,-39.3693" "0.075")
(command "_circle" "4799.0625,-39.0693" "0.075")
(command "_circle" "4798.7625,-40.2693" "0.075")
(command "_circle" "4798.7625,-39.9693" "0.075")
(command "_circle" "4798.7625,-39.6693" "0.075")
(command "_circle" "4798.7625,-39.3693" "0.075")
(command "_circle" "4798.7625,-39.0693" "0.075")
(command "_circle" "4798.4625,-40.2693" "0.075")
(command "_circle" "4798.4625,-39.9693" "0.075")
(command "_circle" "4798.4625,-39.6693" "0.075")
(command "_circle" "4798.4625,-39.3693" "0.075")
(command "_circle" "4798.4625,-39.0693" "0.075")
(command "_circle" "4798.1625,-40.2693" "0.075")
(command "_circle" "4798.1625,-39.9693" "0.075")
(command "_circle" "4798.1625,-39.6693" "0.075")
(command "_circle" "4798.1625,-39.3693" "0.075")
(command "_circle" "4798.1625,-39.0693" "0.075")
(command "_circle" "4797.8625,-40.2693" "0.075")
(command "_circle" "4797.8625,-39.9693" "0.075")
(command "_circle" "4797.8625,-39.6693" "0.075")
(command "_circle" "4797.8625,-39.3693" "0.075")
(command "_circle" "4797.8625,-39.0693" "0.075")
(command "_layer" "set" "nitride" "")
(setq coords (list 
(list 4800.2625 -14.8263) 
(list 4800.2625 100.8184) 
(list 4799.7375 100.8184) 
(list 4799.7375 -14.8263)))
(apply 'command (append '("pline") coords '("c")))
(setq currobj (ssadd (entlast) currobj))
(command "_layer" "set" "prebias" "")
(command "_rectangle" "4799.7375,-14.8263" "4800.2625,100.8184")
(setq currobj (ssadd (entlast) currobj))
(command "_layer" "set" "nitride" "")
(setq coords (list 
(list 4800.2625 100.8184) 
(list 4800.5625 110.8184) 
(list 4800.5625 110.8184) 
(list 4800.5625 111.8184) 
(list 4874.585 111.0684) 
(list 4874.585 116.0114) 
(list 4800.5625 115.2614) 
(list 4800.5625 116.2614) 
(list 4800.5625 116.2614) 
(list 4800.2625 126.2614) 
(list 4799.7375 126.2614) 
(list 4799.4375 116.2614) 
(list 4799.4375 116.2614) 
(list 4799.4375 115.2614) 
(list 4725.415 116.0114) 
(list 4725.415 111.0684) 
(list 4799.4375 111.8184) 
(list 4799.4375 110.8184) 
(list 4799.4375 110.8184) 
(list 4799.7375 100.8184)))
(apply 'command (append '("pline") coords '("c")))
(setq currobj (ssadd (entlast) currobj))
(command "_layer" "set" "prebias" "")
(setq coords (list 
(list 4799.4375 100.8184) 
(list 4799.4375 111.8184) 
(list 4725.415 111.0684) 
(list 4725.415 116.0114) 
(list 4799.4375 115.2614) 
(list 4799.4375 126.2614) 
(list 4800.5625 126.2614) 
(list 4800.5625 115.2614) 
(list 4874.585 116.0114) 
(list 4874.585 111.0684) 
(list 4800.5625 111.8184) 
(list 4800.5625 100.8184)))
(apply 'command (append '("pline") coords '("c")))
(setq currobj (ssadd (entlast) currobj))
(command "_layer" "set" "nitride" "")
(command "_layer" "set" "fda1" "")
(setq coords (list 
(list 4800.5625 111.9614) 
(list 4874.585 111.2114) 
(list 4874.585 111.3884) 
(list 4800.5625 112.0384)))
(apply 'command (append '("pline") coords '("c")))
(setq currobj (ssadd (entlast) currobj))
(setq coords (list 
(list 4800.5625 112.1814) 
(list 4874.585 111.5314) 
(list 4874.585 111.7084) 
(list 4800.5625 112.2584)))
(apply 'command (append '("pline") coords '("c")))
(setq currobj (ssadd (entlast) currobj))
(setq coords (list 
(list 4800.5625 112.4014) 
(list 4874.585 111.8514) 
(list 4874.585 112.0284) 
(list 4800.5625 112.4784)))
(apply 'command (append '("pline") coords '("c")))
(setq currobj (ssadd (entlast) currobj))
(setq coords (list 
(list 4800.5625 112.6214) 
(list 4874.585 112.1714) 
(list 4874.585 112.3484) 
(list 4800.5625 112.6984)))
(apply 'command (append '("pline") coords '("c")))
(setq currobj (ssadd (entlast) currobj))
(setq coords (list 
(list 4800.5625 112.8414) 
(list 4874.585 112.4914) 
(list 4874.585 112.6684) 
(list 4800.5625 112.9184)))
(apply 'command (append '("pline") coords '("c")))
(setq currobj (ssadd (entlast) currobj))
(setq coords (list 
(list 4800.5625 113.0614) 
(list 4874.585 112.8114) 
(list 4874.585 112.9884) 
(list 4800.5625 113.1384)))
(apply 'command (append '("pline") coords '("c")))
(setq currobj (ssadd (entlast) currobj))
(setq coords (list 
(list 4800.5625 113.2814) 
(list 4874.585 113.1314) 
(list 4874.585 113.3084) 
(list 4800.5625 113.3584)))
(apply 'command (append '("pline") coords '("c")))
(setq currobj (ssadd (entlast) currobj))
(setq coords (list 
(list 4800.5625 113.5014) 
(list 4874.585 113.4514) 
(list 4874.585 113.6284) 
(list 4800.5625 113.5784)))
(apply 'command (append '("pline") coords '("c")))
(setq currobj (ssadd (entlast) currobj))
(setq coords (list 
(list 4800.5625 113.7214) 
(list 4874.585 113.7714) 
(list 4874.585 113.9484) 
(list 4800.5625 113.7984)))
(apply 'command (append '("pline") coords '("c")))
(setq currobj (ssadd (entlast) currobj))
(setq coords (list 
(list 4800.5625 113.9414) 
(list 4874.585 114.0914) 
(list 4874.585 114.2684) 
(list 4800.5625 114.0184)))
(apply 'command (append '("pline") coords '("c")))
(setq currobj (ssadd (entlast) currobj))
(setq coords (list 
(list 4800.5625 114.1614) 
(list 4874.585 114.4114) 
(list 4874.585 114.5884) 
(list 4800.5625 114.2384)))
(apply 'command (append '("pline") coords '("c")))
(setq currobj (ssadd (entlast) currobj))
(setq coords (list 
(list 4800.5625 114.3814) 
(list 4874.585 114.7314) 
(list 4874.585 114.9084) 
(list 4800.5625 114.4584)))
(apply 'command (append '("pline") coords '("c")))
(setq currobj (ssadd (entlast) currobj))
(setq coords (list 
(list 4800.5625 114.6014) 
(list 4874.585 115.0514) 
(list 4874.585 115.2284) 
(list 4800.5625 114.6784)))
(apply 'command (append '("pline") coords '("c")))
(setq currobj (ssadd (entlast) currobj))
(setq coords (list 
(list 4800.5625 114.8214) 
(list 4874.585 115.3714) 
(list 4874.585 115.5484) 
(list 4800.5625 114.8984)))
(apply 'command (append '("pline") coords '("c")))
(setq currobj (ssadd (entlast) currobj))
(setq coords (list 
(list 4800.5625 115.0414) 
(list 4874.585 115.6914) 
(list 4874.585 115.8684) 
(list 4800.5625 115.1184)))
(apply 'command (append '("pline") coords '("c")))
(setq currobj (ssadd (entlast) currobj))
(setq coords (list 
(list 4799.4375 115.1184) 
(list 4725.415 115.8684) 
(list 4725.415 115.6914) 
(list 4799.4375 115.0414)))
(apply 'command (append '("pline") coords '("c")))
(setq currobj (ssadd (entlast) currobj))
(setq coords (list 
(list 4799.4375 114.8984) 
(list 4725.415 115.5484) 
(list 4725.415 115.3714) 
(list 4799.4375 114.8214)))
(apply 'command (append '("pline") coords '("c")))
(setq currobj (ssadd (entlast) currobj))
(setq coords (list 
(list 4799.4375 114.6784) 
(list 4725.415 115.2284) 
(list 4725.415 115.0514) 
(list 4799.4375 114.6014)))
(apply 'command (append '("pline") coords '("c")))
(setq currobj (ssadd (entlast) currobj))
(setq coords (list 
(list 4799.4375 114.4584) 
(list 4725.415 114.9084) 
(list 4725.415 114.7314) 
(list 4799.4375 114.3814)))
(apply 'command (append '("pline") coords '("c")))
(setq currobj (ssadd (entlast) currobj))
(setq coords (list 
(list 4799.4375 114.2384) 
(list 4725.415 114.5884) 
(list 4725.415 114.4114) 
(list 4799.4375 114.1614)))
(apply 'command (append '("pline") coords '("c")))
(setq currobj (ssadd (entlast) currobj))
(setq coords (list 
(list 4799.4375 114.0184) 
(list 4725.415 114.2684) 
(list 4725.415 114.0914) 
(list 4799.4375 113.9414)))
(apply 'command (append '("pline") coords '("c")))
(setq currobj (ssadd (entlast) currobj))
(setq coords (list 
(list 4799.4375 113.7984) 
(list 4725.415 113.9484) 
(list 4725.415 113.7714) 
(list 4799.4375 113.7214)))
(apply 'command (append '("pline") coords '("c")))
(setq currobj (ssadd (entlast) currobj))
(setq coords (list 
(list 4799.4375 113.5784) 
(list 4725.415 113.6284) 
(list 4725.415 113.4514) 
(list 4799.4375 113.5014)))
(apply 'command (append '("pline") coords '("c")))
(setq currobj (ssadd (entlast) currobj))
(setq coords (list 
(list 4799.4375 113.3584) 
(list 4725.415 113.3084) 
(list 4725.415 113.1314) 
(list 4799.4375 113.2814)))
(apply 'command (append '("pline") coords '("c")))
(setq currobj (ssadd (entlast) currobj))
(setq coords (list 
(list 4799.4375 113.1384) 
(list 4725.415 112.9884) 
(list 4725.415 112.8114) 
(list 4799.4375 113.0614)))
(apply 'command (append '("pline") coords '("c")))
(setq currobj (ssadd (entlast) currobj))
(setq coords (list 
(list 4799.4375 112.9184) 
(list 4725.415 112.6684) 
(list 4725.415 112.4914) 
(list 4799.4375 112.8414)))
(apply 'command (append '("pline") coords '("c")))
(setq currobj (ssadd (entlast) currobj))
(setq coords (list 
(list 4799.4375 112.6984) 
(list 4725.415 112.3484) 
(list 4725.415 112.1714) 
(list 4799.4375 112.6214)))
(apply 'command (append '("pline") coords '("c")))
(setq currobj (ssadd (entlast) currobj))
(setq coords (list 
(list 4799.4375 112.4784) 
(list 4725.415 112.0284) 
(list 4725.415 111.8514) 
(list 4799.4375 112.4014)))
(apply 'command (append '("pline") coords '("c")))
(setq currobj (ssadd (entlast) currobj))
(setq coords (list 
(list 4799.4375 112.2584) 
(list 4725.415 111.7084) 
(list 4725.415 111.5314) 
(list 4799.4375 112.1814)))
(apply 'command (append '("pline") coords '("c")))
(setq currobj (ssadd (entlast) currobj))
(setq coords (list 
(list 4799.4375 112.0384) 
(list 4725.415 111.3884) 
(list 4725.415 111.2114) 
(list 4799.4375 111.9614)))
(apply 'command (append '("pline") coords '("c")))
(setq currobj (ssadd (entlast) currobj))
(command "_layer" "set" "nitride" "")
(command "_layer" "set" "text" "")
(command "_circle" "4799.0625,100.8184" "0.075")
(command "_circle" "4799.0625,101.1184" "0.075")
(command "_circle" "4799.0625,101.4184" "0.075")
(command "_circle" "4799.0625,101.7184" "0.075")
(command "_circle" "4799.0625,102.0184" "0.075")
(command "_circle" "4798.7625,100.8184" "0.075")
(command "_circle" "4798.7625,101.1184" "0.075")
(command "_circle" "4798.7625,101.4184" "0.075")
(command "_circle" "4798.7625,101.7184" "0.075")
(command "_circle" "4798.7625,102.0184" "0.075")
(command "_circle" "4798.4625,100.8184" "0.075")
(command "_circle" "4798.4625,101.1184" "0.075")
(command "_circle" "4798.4625,101.4184" "0.075")
(command "_circle" "4798.4625,101.7184" "0.075")
(command "_circle" "4798.4625,102.0184" "0.075")
(command "_circle" "4798.1625,100.8184" "0.075")
(command "_circle" "4798.1625,101.1184" "0.075")
(command "_circle" "4798.1625,101.4184" "0.075")
(command "_circle" "4798.1625,101.7184" "0.075")
(command "_circle" "4798.1625,102.0184" "0.075")
(command "_circle" "4797.8625,100.8184" "0.075")
(command "_circle" "4797.8625,101.1184" "0.075")
(command "_circle" "4797.8625,101.4184" "0.075")
(command "_circle" "4797.8625,101.7184" "0.075")
(command "_circle" "4797.8625,102.0184" "0.075")
(command "_layer" "set" "nitride" "")
(setq coords (list 
(list 4800.2625 126.2614) 
(list 4800.2625 241.9061) 
(list 4799.7375 241.9061) 
(list 4799.7375 126.2614)))
(apply 'command (append '("pline") coords '("c")))
(setq currobj (ssadd (entlast) currobj))
(command "_layer" "set" "prebias" "")
(command "_rectangle" "4799.7375,126.2614" "4800.2625,241.9061")
(setq currobj (ssadd (entlast) currobj))
(command "_layer" "set" "nitride" "")
(setq coords (list 
(list 4800.2625 241.9061) 
(list 4800.5625 251.9061) 
(list 4800.5625 251.9061) 
(list 4800.5625 252.9061) 
(list 4874.585 252.1561) 
(list 4874.585 257.0991) 
(list 4800.5625 256.3491) 
(list 4800.5625 257.3491) 
(list 4800.5625 257.3491) 
(list 4800.2625 267.3491) 
(list 4799.7375 267.3491) 
(list 4799.4375 257.3491) 
(list 4799.4375 257.3491) 
(list 4799.4375 256.3491) 
(list 4725.415 257.0991) 
(list 4725.415 252.1561) 
(list 4799.4375 252.9061) 
(list 4799.4375 251.9061) 
(list 4799.4375 251.9061) 
(list 4799.7375 241.9061)))
(apply 'command (append '("pline") coords '("c")))
(setq currobj (ssadd (entlast) currobj))
(command "_layer" "set" "prebias" "")
(setq coords (list 
(list 4799.4375 241.9061) 
(list 4799.4375 252.9061) 
(list 4725.415 252.1561) 
(list 4725.415 257.0991) 
(list 4799.4375 256.3491) 
(list 4799.4375 267.3491) 
(list 4800.5625 267.3491) 
(list 4800.5625 256.3491) 
(list 4874.585 257.0991) 
(list 4874.585 252.1561) 
(list 4800.5625 252.9061) 
(list 4800.5625 241.9061)))
(apply 'command (append '("pline") coords '("c")))
(setq currobj (ssadd (entlast) currobj))
(command "_layer" "set" "nitride" "")
(command "_layer" "set" "fda1" "")
(setq coords (list 
(list 4800.5625 253.0491) 
(list 4874.585 252.2991) 
(list 4874.585 252.4761) 
(list 4800.5625 253.1261)))
(apply 'command (append '("pline") coords '("c")))
(setq currobj (ssadd (entlast) currobj))
(setq coords (list 
(list 4800.5625 253.2691) 
(list 4874.585 252.6191) 
(list 4874.585 252.7961) 
(list 4800.5625 253.3461)))
(apply 'command (append '("pline") coords '("c")))
(setq currobj (ssadd (entlast) currobj))
(setq coords (list 
(list 4800.5625 253.4891) 
(list 4874.585 252.9391) 
(list 4874.585 253.1161) 
(list 4800.5625 253.5661)))
(apply 'command (append '("pline") coords '("c")))
(setq currobj (ssadd (entlast) currobj))
(setq coords (list 
(list 4800.5625 253.7091) 
(list 4874.585 253.2591) 
(list 4874.585 253.4361) 
(list 4800.5625 253.7861)))
(apply 'command (append '("pline") coords '("c")))
(setq currobj (ssadd (entlast) currobj))
(setq coords (list 
(list 4800.5625 253.9291) 
(list 4874.585 253.5791) 
(list 4874.585 253.7561) 
(list 4800.5625 254.0061)))
(apply 'command (append '("pline") coords '("c")))
(setq currobj (ssadd (entlast) currobj))
(setq coords (list 
(list 4800.5625 254.1491) 
(list 4874.585 253.8991) 
(list 4874.585 254.0761) 
(list 4800.5625 254.2261)))
(apply 'command (append '("pline") coords '("c")))
(setq currobj (ssadd (entlast) currobj))
(setq coords (list 
(list 4800.5625 254.3691) 
(list 4874.585 254.2191) 
(list 4874.585 254.3961) 
(list 4800.5625 254.4461)))
(apply 'command (append '("pline") coords '("c")))
(setq currobj (ssadd (entlast) currobj))
(setq coords (list 
(list 4800.5625 254.5891) 
(list 4874.585 254.5391) 
(list 4874.585 254.7161) 
(list 4800.5625 254.6661)))
(apply 'command (append '("pline") coords '("c")))
(setq currobj (ssadd (entlast) currobj))
(setq coords (list 
(list 4800.5625 254.8091) 
(list 4874.585 254.8591) 
(list 4874.585 255.0361) 
(list 4800.5625 254.8861)))
(apply 'command (append '("pline") coords '("c")))
(setq currobj (ssadd (entlast) currobj))
(setq coords (list 
(list 4800.5625 255.0291) 
(list 4874.585 255.1791) 
(list 4874.585 255.3561) 
(list 4800.5625 255.1061)))
(apply 'command (append '("pline") coords '("c")))
(setq currobj (ssadd (entlast) currobj))
(setq coords (list 
(list 4800.5625 255.2491) 
(list 4874.585 255.4991) 
(list 4874.585 255.6761) 
(list 4800.5625 255.3261)))
(apply 'command (append '("pline") coords '("c")))
(setq currobj (ssadd (entlast) currobj))
(setq coords (list 
(list 4800.5625 255.4691) 
(list 4874.585 255.8191) 
(list 4874.585 255.9961) 
(list 4800.5625 255.5461)))
(apply 'command (append '("pline") coords '("c")))
(setq currobj (ssadd (entlast) currobj))
(setq coords (list 
(list 4800.5625 255.6891) 
(list 4874.585 256.1391) 
(list 4874.585 256.3161) 
(list 4800.5625 255.7661)))
(apply 'command (append '("pline") coords '("c")))
(setq currobj (ssadd (entlast) currobj))
(setq coords (list 
(list 4800.5625 255.9091) 
(list 4874.585 256.4591) 
(list 4874.585 256.6361) 
(list 4800.5625 255.9861)))
(apply 'command (append '("pline") coords '("c")))
(setq currobj (ssadd (entlast) currobj))
(setq coords (list 
(list 4800.5625 256.1291) 
(list 4874.585 256.7791) 
(list 4874.585 256.9561) 
(list 4800.5625 256.2061)))
(apply 'command (append '("pline") coords '("c")))
(setq currobj (ssadd (entlast) currobj))
(setq coords (list 
(list 4799.4375 256.2061) 
(list 4725.415 256.9561) 
(list 4725.415 256.7791) 
(list 4799.4375 256.1291)))
(apply 'command (append '("pline") coords '("c")))
(setq currobj (ssadd (entlast) currobj))
(setq coords (list 
(list 4799.4375 255.9861) 
(list 4725.415 256.6361) 
(list 4725.415 256.4591) 
(list 4799.4375 255.9091)))
(apply 'command (append '("pline") coords '("c")))
(setq currobj (ssadd (entlast) currobj))
(setq coords (list 
(list 4799.4375 255.7661) 
(list 4725.415 256.3161) 
(list 4725.415 256.1391) 
(list 4799.4375 255.6891)))
(apply 'command (append '("pline") coords '("c")))
(setq currobj (ssadd (entlast) currobj))
(setq coords (list 
(list 4799.4375 255.5461) 
(list 4725.415 255.9961) 
(list 4725.415 255.8191) 
(list 4799.4375 255.4691)))
(apply 'command (append '("pline") coords '("c")))
(setq currobj (ssadd (entlast) currobj))
(setq coords (list 
(list 4799.4375 255.3261) 
(list 4725.415 255.6761) 
(list 4725.415 255.4991) 
(list 4799.4375 255.2491)))
(apply 'command (append '("pline") coords '("c")))
(setq currobj (ssadd (entlast) currobj))
(setq coords (list 
(list 4799.4375 255.1061) 
(list 4725.415 255.3561) 
(list 4725.415 255.1791) 
(list 4799.4375 255.0291)))
(apply 'command (append '("pline") coords '("c")))
(setq currobj (ssadd (entlast) currobj))
(setq coords (list 
(list 4799.4375 254.8861) 
(list 4725.415 255.0361) 
(list 4725.415 254.8591) 
(list 4799.4375 254.8091)))
(apply 'command (append '("pline") coords '("c")))
(setq currobj (ssadd (entlast) currobj))
(setq coords (list 
(list 4799.4375 254.6661) 
(list 4725.415 254.7161) 
(list 4725.415 254.5391) 
(list 4799.4375 254.5891)))
(apply 'command (append '("pline") coords '("c")))
(setq currobj (ssadd (entlast) currobj))
(setq coords (list 
(list 4799.4375 254.4461) 
(list 4725.415 254.3961) 
(list 4725.415 254.2191) 
(list 4799.4375 254.3691)))
(apply 'command (append '("pline") coords '("c")))
(setq currobj (ssadd (entlast) currobj))
(setq coords (list 
(list 4799.4375 254.2261) 
(list 4725.415 254.0761) 
(list 4725.415 253.8991) 
(list 4799.4375 254.1491)))
(apply 'command (append '("pline") coords '("c")))
(setq currobj (ssadd (entlast) currobj))
(setq coords (list 
(list 4799.4375 254.0061) 
(list 4725.415 253.7561) 
(list 4725.415 253.5791) 
(list 4799.4375 253.9291)))
(apply 'command (append '("pline") coords '("c")))
(setq currobj (ssadd (entlast) currobj))
(setq coords (list 
(list 4799.4375 253.7861) 
(list 4725.415 253.4361) 
(list 4725.415 253.2591) 
(list 4799.4375 253.7091)))
(apply 'command (append '("pline") coords '("c")))
(setq currobj (ssadd (entlast) currobj))
(setq coords (list 
(list 4799.4375 253.5661) 
(list 4725.415 253.1161) 
(list 4725.415 252.9391) 
(list 4799.4375 253.4891)))
(apply 'command (append '("pline") coords '("c")))
(setq currobj (ssadd (entlast) currobj))
(setq coords (list 
(list 4799.4375 253.3461) 
(list 4725.415 252.7961) 
(list 4725.415 252.6191) 
(list 4799.4375 253.2691)))
(apply 'command (append '("pline") coords '("c")))
(setq currobj (ssadd (entlast) currobj))
(setq coords (list 
(list 4799.4375 253.1261) 
(list 4725.415 252.4761) 
(list 4725.415 252.2991) 
(list 4799.4375 253.0491)))
(apply 'command (append '("pline") coords '("c")))
(setq currobj (ssadd (entlast) currobj))
(command "_layer" "set" "nitride" "")
(command "_layer" "set" "text" "")
(command "_circle" "4799.0625,241.9061" "0.075")
(command "_circle" "4799.0625,242.2061" "0.075")
(command "_circle" "4799.0625,242.5061" "0.075")
(command "_circle" "4799.0625,242.8061" "0.075")
(command "_circle" "4799.0625,243.1061" "0.075")
(command "_circle" "4798.7625,241.9061" "0.075")
(command "_circle" "4798.7625,242.2061" "0.075")
(command "_circle" "4798.7625,242.5061" "0.075")
(command "_circle" "4798.7625,242.8061" "0.075")
(command "_circle" "4798.7625,243.1061" "0.075")
(command "_circle" "4798.4625,241.9061" "0.075")
(command "_circle" "4798.4625,242.2061" "0.075")
(command "_circle" "4798.4625,242.5061" "0.075")
(command "_circle" "4798.4625,242.8061" "0.075")
(command "_circle" "4798.4625,243.1061" "0.075")
(command "_circle" "4798.1625,241.9061" "0.075")
(command "_circle" "4798.1625,242.2061" "0.075")
(command "_circle" "4798.1625,242.5061" "0.075")
(command "_circle" "4798.1625,242.8061" "0.075")
(command "_circle" "4798.1625,243.1061" "0.075")
(command "_circle" "4797.8625,241.9061" "0.075")
(command "_circle" "4797.8625,242.2061" "0.075")
(command "_circle" "4797.8625,242.5061" "0.075")
(command "_circle" "4797.8625,242.8061" "0.075")
(command "_circle" "4797.8625,243.1061" "0.075")
(command "_layer" "set" "nitride" "")
(setq coords (list 
(list 4800.2625 267.3491) 
(list 4800.2625 382.9939) 
(list 4799.7375 382.9939) 
(list 4799.7375 267.3491)))
(apply 'command (append '("pline") coords '("c")))
(setq currobj (ssadd (entlast) currobj))
(command "_layer" "set" "prebias" "")
(command "_rectangle" "4799.7375,267.3491" "4800.2625,382.9939")
(setq currobj (ssadd (entlast) currobj))
(command "_layer" "set" "nitride" "")
(setq coords (list 
(list 4800.2625 382.9939) 
(list 4800.5625 392.9939) 
(list 4800.5625 392.9939) 
(list 4800.5625 393.9939) 
(list 4874.585 393.2439) 
(list 4874.585 398.1869) 
(list 4800.5625 397.4369) 
(list 4800.5625 398.4369) 
(list 4800.5625 398.4369) 
(list 4800.2625 408.4369) 
(list 4799.7375 408.4369) 
(list 4799.4375 398.4369) 
(list 4799.4375 398.4369) 
(list 4799.4375 397.4369) 
(list 4725.415 398.1869) 
(list 4725.415 393.2439) 
(list 4799.4375 393.9939) 
(list 4799.4375 392.9939) 
(list 4799.4375 392.9939) 
(list 4799.7375 382.9939)))
(apply 'command (append '("pline") coords '("c")))
(setq currobj (ssadd (entlast) currobj))
(command "_layer" "set" "prebias" "")
(setq coords (list 
(list 4799.4375 382.9939) 
(list 4799.4375 393.9939) 
(list 4725.415 393.2439) 
(list 4725.415 398.1869) 
(list 4799.4375 397.4369) 
(list 4799.4375 408.4369) 
(list 4800.5625 408.4369) 
(list 4800.5625 397.4369) 
(list 4874.585 398.1869) 
(list 4874.585 393.2439) 
(list 4800.5625 393.9939) 
(list 4800.5625 382.9939)))
(apply 'command (append '("pline") coords '("c")))
(setq currobj (ssadd (entlast) currobj))
(command "_layer" "set" "nitride" "")
(command "_layer" "set" "fda1" "")
(setq coords (list 
(list 4800.5625 394.1369) 
(list 4874.585 393.3869) 
(list 4874.585 393.5639) 
(list 4800.5625 394.2139)))
(apply 'command (append '("pline") coords '("c")))
(setq currobj (ssadd (entlast) currobj))
(setq coords (list 
(list 4800.5625 394.3569) 
(list 4874.585 393.7069) 
(list 4874.585 393.8839) 
(list 4800.5625 394.4339)))
(apply 'command (append '("pline") coords '("c")))
(setq currobj (ssadd (entlast) currobj))
(setq coords (list 
(list 4800.5625 394.5769) 
(list 4874.585 394.0269) 
(list 4874.585 394.2039) 
(list 4800.5625 394.6539)))
(apply 'command (append '("pline") coords '("c")))
(setq currobj (ssadd (entlast) currobj))
(setq coords (list 
(list 4800.5625 394.7969) 
(list 4874.585 394.3469) 
(list 4874.585 394.5239) 
(list 4800.5625 394.8739)))
(apply 'command (append '("pline") coords '("c")))
(setq currobj (ssadd (entlast) currobj))
(setq coords (list 
(list 4800.5625 395.0169) 
(list 4874.585 394.6669) 
(list 4874.585 394.8439) 
(list 4800.5625 395.0939)))
(apply 'command (append '("pline") coords '("c")))
(setq currobj (ssadd (entlast) currobj))
(setq coords (list 
(list 4800.5625 395.2369) 
(list 4874.585 394.9869) 
(list 4874.585 395.1639) 
(list 4800.5625 395.3139)))
(apply 'command (append '("pline") coords '("c")))
(setq currobj (ssadd (entlast) currobj))
(setq coords (list 
(list 4800.5625 395.4569) 
(list 4874.585 395.3069) 
(list 4874.585 395.4839) 
(list 4800.5625 395.5339)))
(apply 'command (append '("pline") coords '("c")))
(setq currobj (ssadd (entlast) currobj))
(setq coords (list 
(list 4800.5625 395.6769) 
(list 4874.585 395.6269) 
(list 4874.585 395.8039) 
(list 4800.5625 395.7539)))
(apply 'command (append '("pline") coords '("c")))
(setq currobj (ssadd (entlast) currobj))
(setq coords (list 
(list 4800.5625 395.8969) 
(list 4874.585 395.9469) 
(list 4874.585 396.1239) 
(list 4800.5625 395.9739)))
(apply 'command (append '("pline") coords '("c")))
(setq currobj (ssadd (entlast) currobj))
(setq coords (list 
(list 4800.5625 396.1169) 
(list 4874.585 396.2669) 
(list 4874.585 396.4439) 
(list 4800.5625 396.1939)))
(apply 'command (append '("pline") coords '("c")))
(setq currobj (ssadd (entlast) currobj))
(setq coords (list 
(list 4800.5625 396.3369) 
(list 4874.585 396.5869) 
(list 4874.585 396.7639) 
(list 4800.5625 396.4139)))
(apply 'command (append '("pline") coords '("c")))
(setq currobj (ssadd (entlast) currobj))
(setq coords (list 
(list 4800.5625 396.5569) 
(list 4874.585 396.9069) 
(list 4874.585 397.0839) 
(list 4800.5625 396.6339)))
(apply 'command (append '("pline") coords '("c")))
(setq currobj (ssadd (entlast) currobj))
(setq coords (list 
(list 4800.5625 396.7769) 
(list 4874.585 397.2269) 
(list 4874.585 397.4039) 
(list 4800.5625 396.8539)))
(apply 'command (append '("pline") coords '("c")))
(setq currobj (ssadd (entlast) currobj))
(setq coords (list 
(list 4800.5625 396.9969) 
(list 4874.585 397.5469) 
(list 4874.585 397.7239) 
(list 4800.5625 397.0739)))
(apply 'command (append '("pline") coords '("c")))
(setq currobj (ssadd (entlast) currobj))
(setq coords (list 
(list 4800.5625 397.2169) 
(list 4874.585 397.8669) 
(list 4874.585 398.0439) 
(list 4800.5625 397.2939)))
(apply 'command (append '("pline") coords '("c")))
(setq currobj (ssadd (entlast) currobj))
(setq coords (list 
(list 4799.4375 397.2939) 
(list 4725.415 398.0439) 
(list 4725.415 397.8669) 
(list 4799.4375 397.2169)))
(apply 'command (append '("pline") coords '("c")))
(setq currobj (ssadd (entlast) currobj))
(setq coords (list 
(list 4799.4375 397.0739) 
(list 4725.415 397.7239) 
(list 4725.415 397.5469) 
(list 4799.4375 396.9969)))
(apply 'command (append '("pline") coords '("c")))
(setq currobj (ssadd (entlast) currobj))
(setq coords (list 
(list 4799.4375 396.8539) 
(list 4725.415 397.4039) 
(list 4725.415 397.2269) 
(list 4799.4375 396.7769)))
(apply 'command (append '("pline") coords '("c")))
(setq currobj (ssadd (entlast) currobj))
(setq coords (list 
(list 4799.4375 396.6339) 
(list 4725.415 397.0839) 
(list 4725.415 396.9069) 
(list 4799.4375 396.5569)))
(apply 'command (append '("pline") coords '("c")))
(setq currobj (ssadd (entlast) currobj))
(setq coords (list 
(list 4799.4375 396.4139) 
(list 4725.415 396.7639) 
(list 4725.415 396.5869) 
(list 4799.4375 396.3369)))
(apply 'command (append '("pline") coords '("c")))
(setq currobj (ssadd (entlast) currobj))
(setq coords (list 
(list 4799.4375 396.1939) 
(list 4725.415 396.4439) 
(list 4725.415 396.2669) 
(list 4799.4375 396.1169)))
(apply 'command (append '("pline") coords '("c")))
(setq currobj (ssadd (entlast) currobj))
(setq coords (list 
(list 4799.4375 395.9739) 
(list 4725.415 396.1239) 
(list 4725.415 395.9469) 
(list 4799.4375 395.8969)))
(apply 'command (append '("pline") coords '("c")))
(setq currobj (ssadd (entlast) currobj))
(setq coords (list 
(list 4799.4375 395.7539) 
(list 4725.415 395.8039) 
(list 4725.415 395.6269) 
(list 4799.4375 395.6769)))
(apply 'command (append '("pline") coords '("c")))
(setq currobj (ssadd (entlast) currobj))
(setq coords (list 
(list 4799.4375 395.5339) 
(list 4725.415 395.4839) 
(list 4725.415 395.3069) 
(list 4799.4375 395.4569)))
(apply 'command (append '("pline") coords '("c")))
(setq currobj (ssadd (entlast) currobj))
(setq coords (list 
(list 4799.4375 395.3139) 
(list 4725.415 395.1639) 
(list 4725.415 394.9869) 
(list 4799.4375 395.2369)))
(apply 'command (append '("pline") coords '("c")))
(setq currobj (ssadd (entlast) currobj))
(setq coords (list 
(list 4799.4375 395.0939) 
(list 4725.415 394.8439) 
(list 4725.415 394.6669) 
(list 4799.4375 395.0169)))
(apply 'command (append '("pline") coords '("c")))
(setq currobj (ssadd (entlast) currobj))
(setq coords (list 
(list 4799.4375 394.8739) 
(list 4725.415 394.5239) 
(list 4725.415 394.3469) 
(list 4799.4375 394.7969)))
(apply 'command (append '("pline") coords '("c")))
(setq currobj (ssadd (entlast) currobj))
(setq coords (list 
(list 4799.4375 394.6539) 
(list 4725.415 394.2039) 
(list 4725.415 394.0269) 
(list 4799.4375 394.5769)))
(apply 'command (append '("pline") coords '("c")))
(setq currobj (ssadd (entlast) currobj))
(setq coords (list 
(list 4799.4375 394.4339) 
(list 4725.415 393.8839) 
(list 4725.415 393.7069) 
(list 4799.4375 394.3569)))
(apply 'command (append '("pline") coords '("c")))
(setq currobj (ssadd (entlast) currobj))
(setq coords (list 
(list 4799.4375 394.2139) 
(list 4725.415 393.5639) 
(list 4725.415 393.3869) 
(list 4799.4375 394.1369)))
(apply 'command (append '("pline") coords '("c")))
(setq currobj (ssadd (entlast) currobj))
(command "_layer" "set" "nitride" "")
(command "_layer" "set" "text" "")
(command "_circle" "4799.0625,382.9939" "0.075")
(command "_circle" "4799.0625,383.2939" "0.075")
(command "_circle" "4799.0625,383.5939" "0.075")
(command "_circle" "4799.0625,383.8939" "0.075")
(command "_circle" "4799.0625,384.1939" "0.075")
(command "_circle" "4798.7625,382.9939" "0.075")
(command "_circle" "4798.7625,383.2939" "0.075")
(command "_circle" "4798.7625,383.5939" "0.075")
(command "_circle" "4798.7625,383.8939" "0.075")
(command "_circle" "4798.7625,384.1939" "0.075")
(command "_circle" "4798.4625,382.9939" "0.075")
(command "_circle" "4798.4625,383.2939" "0.075")
(command "_circle" "4798.4625,383.5939" "0.075")
(command "_circle" "4798.4625,383.8939" "0.075")
(command "_circle" "4798.4625,384.1939" "0.075")
(command "_circle" "4798.1625,382.9939" "0.075")
(command "_circle" "4798.1625,383.2939" "0.075")
(command "_circle" "4798.1625,383.5939" "0.075")
(command "_circle" "4798.1625,383.8939" "0.075")
(command "_circle" "4798.1625,384.1939" "0.075")
(command "_circle" "4797.8625,382.9939" "0.075")
(command "_circle" "4797.8625,383.2939" "0.075")
(command "_circle" "4797.8625,383.5939" "0.075")
(command "_circle" "4797.8625,383.8939" "0.075")
(command "_circle" "4797.8625,384.1939" "0.075")
(command "_layer" "set" "nitride" "")
(setq coords (list 
(list 4800.2625 408.4369) 
(list 4800.2625 524.0816) 
(list 4799.7375 524.0816) 
(list 4799.7375 408.4369)))
(apply 'command (append '("pline") coords '("c")))
(setq currobj (ssadd (entlast) currobj))
(command "_layer" "set" "prebias" "")
(command "_rectangle" "4799.7375,408.4369" "4800.2625,524.0816")
(setq currobj (ssadd (entlast) currobj))
(command "_layer" "set" "nitride" "")
(setq coords (list 
(list 4800.2625 524.0816) 
(list 4800.5625 534.0816) 
(list 4800.5625 534.0816) 
(list 4800.5625 535.0816) 
(list 4874.585 534.3316) 
(list 4874.585 539.2746) 
(list 4800.5625 538.5246) 
(list 4800.5625 539.5246) 
(list 4800.5625 539.5246) 
(list 4800.2625 549.5246) 
(list 4799.7375 549.5246) 
(list 4799.4375 539.5246) 
(list 4799.4375 539.5246) 
(list 4799.4375 538.5246) 
(list 4725.415 539.2746) 
(list 4725.415 534.3316) 
(list 4799.4375 535.0816) 
(list 4799.4375 534.0816) 
(list 4799.4375 534.0816) 
(list 4799.7375 524.0816)))
(apply 'command (append '("pline") coords '("c")))
(setq currobj (ssadd (entlast) currobj))
(command "_layer" "set" "prebias" "")
(setq coords (list 
(list 4799.4375 524.0816) 
(list 4799.4375 535.0816) 
(list 4725.415 534.3316) 
(list 4725.415 539.2746) 
(list 4799.4375 538.5246) 
(list 4799.4375 549.5246) 
(list 4800.5625 549.5246) 
(list 4800.5625 538.5246) 
(list 4874.585 539.2746) 
(list 4874.585 534.3316) 
(list 4800.5625 535.0816) 
(list 4800.5625 524.0816)))
(apply 'command (append '("pline") coords '("c")))
(setq currobj (ssadd (entlast) currobj))
(command "_layer" "set" "nitride" "")
(command "_layer" "set" "fda1" "")
(setq coords (list 
(list 4800.5625 535.2246) 
(list 4874.585 534.4746) 
(list 4874.585 534.6516) 
(list 4800.5625 535.3016)))
(apply 'command (append '("pline") coords '("c")))
(setq currobj (ssadd (entlast) currobj))
(setq coords (list 
(list 4800.5625 535.4446) 
(list 4874.585 534.7946) 
(list 4874.585 534.9716) 
(list 4800.5625 535.5216)))
(apply 'command (append '("pline") coords '("c")))
(setq currobj (ssadd (entlast) currobj))
(setq coords (list 
(list 4800.5625 535.6646) 
(list 4874.585 535.1146) 
(list 4874.585 535.2916) 
(list 4800.5625 535.7416)))
(apply 'command (append '("pline") coords '("c")))
(setq currobj (ssadd (entlast) currobj))
(setq coords (list 
(list 4800.5625 535.8846) 
(list 4874.585 535.4346) 
(list 4874.585 535.6116) 
(list 4800.5625 535.9616)))
(apply 'command (append '("pline") coords '("c")))
(setq currobj (ssadd (entlast) currobj))
(setq coords (list 
(list 4800.5625 536.1046) 
(list 4874.585 535.7546) 
(list 4874.585 535.9316) 
(list 4800.5625 536.1816)))
(apply 'command (append '("pline") coords '("c")))
(setq currobj (ssadd (entlast) currobj))
(setq coords (list 
(list 4800.5625 536.3246) 
(list 4874.585 536.0746) 
(list 4874.585 536.2516) 
(list 4800.5625 536.4016)))
(apply 'command (append '("pline") coords '("c")))
(setq currobj (ssadd (entlast) currobj))
(setq coords (list 
(list 4800.5625 536.5446) 
(list 4874.585 536.3946) 
(list 4874.585 536.5716) 
(list 4800.5625 536.6216)))
(apply 'command (append '("pline") coords '("c")))
(setq currobj (ssadd (entlast) currobj))
(setq coords (list 
(list 4800.5625 536.7646) 
(list 4874.585 536.7146) 
(list 4874.585 536.8916) 
(list 4800.5625 536.8416)))
(apply 'command (append '("pline") coords '("c")))
(setq currobj (ssadd (entlast) currobj))
(setq coords (list 
(list 4800.5625 536.9846) 
(list 4874.585 537.0346) 
(list 4874.585 537.2116) 
(list 4800.5625 537.0616)))
(apply 'command (append '("pline") coords '("c")))
(setq currobj (ssadd (entlast) currobj))
(setq coords (list 
(list 4800.5625 537.2046) 
(list 4874.585 537.3546) 
(list 4874.585 537.5316) 
(list 4800.5625 537.2816)))
(apply 'command (append '("pline") coords '("c")))
(setq currobj (ssadd (entlast) currobj))
(setq coords (list 
(list 4800.5625 537.4246) 
(list 4874.585 537.6746) 
(list 4874.585 537.8516) 
(list 4800.5625 537.5016)))
(apply 'command (append '("pline") coords '("c")))
(setq currobj (ssadd (entlast) currobj))
(setq coords (list 
(list 4800.5625 537.6446) 
(list 4874.585 537.9946) 
(list 4874.585 538.1716) 
(list 4800.5625 537.7216)))
(apply 'command (append '("pline") coords '("c")))
(setq currobj (ssadd (entlast) currobj))
(setq coords (list 
(list 4800.5625 537.8646) 
(list 4874.585 538.3146) 
(list 4874.585 538.4916) 
(list 4800.5625 537.9416)))
(apply 'command (append '("pline") coords '("c")))
(setq currobj (ssadd (entlast) currobj))
(setq coords (list 
(list 4800.5625 538.0846) 
(list 4874.585 538.6346) 
(list 4874.585 538.8116) 
(list 4800.5625 538.1616)))
(apply 'command (append '("pline") coords '("c")))
(setq currobj (ssadd (entlast) currobj))
(setq coords (list 
(list 4800.5625 538.3046) 
(list 4874.585 538.9546) 
(list 4874.585 539.1316) 
(list 4800.5625 538.3816)))
(apply 'command (append '("pline") coords '("c")))
(setq currobj (ssadd (entlast) currobj))
(setq coords (list 
(list 4799.4375 538.3816) 
(list 4725.415 539.1316) 
(list 4725.415 538.9546) 
(list 4799.4375 538.3046)))
(apply 'command (append '("pline") coords '("c")))
(setq currobj (ssadd (entlast) currobj))
(setq coords (list 
(list 4799.4375 538.1616) 
(list 4725.415 538.8116) 
(list 4725.415 538.6346) 
(list 4799.4375 538.0846)))
(apply 'command (append '("pline") coords '("c")))
(setq currobj (ssadd (entlast) currobj))
(setq coords (list 
(list 4799.4375 537.9416) 
(list 4725.415 538.4916) 
(list 4725.415 538.3146) 
(list 4799.4375 537.8646)))
(apply 'command (append '("pline") coords '("c")))
(setq currobj (ssadd (entlast) currobj))
(setq coords (list 
(list 4799.4375 537.7216) 
(list 4725.415 538.1716) 
(list 4725.415 537.9946) 
(list 4799.4375 537.6446)))
(apply 'command (append '("pline") coords '("c")))
(setq currobj (ssadd (entlast) currobj))
(setq coords (list 
(list 4799.4375 537.5016) 
(list 4725.415 537.8516) 
(list 4725.415 537.6746) 
(list 4799.4375 537.4246)))
(apply 'command (append '("pline") coords '("c")))
(setq currobj (ssadd (entlast) currobj))
(setq coords (list 
(list 4799.4375 537.2816) 
(list 4725.415 537.5316) 
(list 4725.415 537.3546) 
(list 4799.4375 537.2046)))
(apply 'command (append '("pline") coords '("c")))
(setq currobj (ssadd (entlast) currobj))
(setq coords (list 
(list 4799.4375 537.0616) 
(list 4725.415 537.2116) 
(list 4725.415 537.0346) 
(list 4799.4375 536.9846)))
(apply 'command (append '("pline") coords '("c")))
(setq currobj (ssadd (entlast) currobj))
(setq coords (list 
(list 4799.4375 536.8416) 
(list 4725.415 536.8916) 
(list 4725.415 536.7146) 
(list 4799.4375 536.7646)))
(apply 'command (append '("pline") coords '("c")))
(setq currobj (ssadd (entlast) currobj))
(setq coords (list 
(list 4799.4375 536.6216) 
(list 4725.415 536.5716) 
(list 4725.415 536.3946) 
(list 4799.4375 536.5446)))
(apply 'command (append '("pline") coords '("c")))
(setq currobj (ssadd (entlast) currobj))
(setq coords (list 
(list 4799.4375 536.4016) 
(list 4725.415 536.2516) 
(list 4725.415 536.0746) 
(list 4799.4375 536.3246)))
(apply 'command (append '("pline") coords '("c")))
(setq currobj (ssadd (entlast) currobj))
(setq coords (list 
(list 4799.4375 536.1816) 
(list 4725.415 535.9316) 
(list 4725.415 535.7546) 
(list 4799.4375 536.1046)))
(apply 'command (append '("pline") coords '("c")))
(setq currobj (ssadd (entlast) currobj))
(setq coords (list 
(list 4799.4375 535.9616) 
(list 4725.415 535.6116) 
(list 4725.415 535.4346) 
(list 4799.4375 535.8846)))
(apply 'command (append '("pline") coords '("c")))
(setq currobj (ssadd (entlast) currobj))
(setq coords (list 
(list 4799.4375 535.7416) 
(list 4725.415 535.2916) 
(list 4725.415 535.1146) 
(list 4799.4375 535.6646)))
(apply 'command (append '("pline") coords '("c")))
(setq currobj (ssadd (entlast) currobj))
(setq coords (list 
(list 4799.4375 535.5216) 
(list 4725.415 534.9716) 
(list 4725.415 534.7946) 
(list 4799.4375 535.4446)))
(apply 'command (append '("pline") coords '("c")))
(setq currobj (ssadd (entlast) currobj))
(setq coords (list 
(list 4799.4375 535.3016) 
(list 4725.415 534.6516) 
(list 4725.415 534.4746) 
(list 4799.4375 535.2246)))
(apply 'command (append '("pline") coords '("c")))
(setq currobj (ssadd (entlast) currobj))
(command "_layer" "set" "nitride" "")
(command "_layer" "set" "text" "")
(command "_circle" "4799.0625,524.0816" "0.075")
(command "_circle" "4799.0625,524.3816" "0.075")
(command "_circle" "4799.0625,524.6816" "0.075")
(command "_circle" "4799.0625,524.9816" "0.075")
(command "_circle" "4799.0625,525.2816" "0.075")
(command "_circle" "4798.7625,524.0816" "0.075")
(command "_circle" "4798.7625,524.3816" "0.075")
(command "_circle" "4798.7625,524.6816" "0.075")
(command "_circle" "4798.7625,524.9816" "0.075")
(command "_circle" "4798.7625,525.2816" "0.075")
(command "_circle" "4798.4625,524.0816" "0.075")
(command "_circle" "4798.4625,524.3816" "0.075")
(command "_circle" "4798.4625,524.6816" "0.075")
(command "_circle" "4798.4625,524.9816" "0.075")
(command "_circle" "4798.4625,525.2816" "0.075")
(command "_circle" "4798.1625,524.0816" "0.075")
(command "_circle" "4798.1625,524.3816" "0.075")
(command "_circle" "4798.1625,524.6816" "0.075")
(command "_circle" "4798.1625,524.9816" "0.075")
(command "_circle" "4798.1625,525.2816" "0.075")
(command "_circle" "4797.8625,524.0816" "0.075")
(command "_circle" "4797.8625,524.3816" "0.075")
(command "_circle" "4797.8625,524.6816" "0.075")
(command "_circle" "4797.8625,524.9816" "0.075")
(command "_circle" "4797.8625,525.2816" "0.075")
(command "_layer" "set" "nitride" "")
(setq coords (list 
(list 4800.2625 549.5246) 
(list 4800.2625 665.1693) 
(list 4799.7375 665.1693) 
(list 4799.7375 549.5246)))
(apply 'command (append '("pline") coords '("c")))
(setq currobj (ssadd (entlast) currobj))
(command "_layer" "set" "prebias" "")
(command "_rectangle" "4799.7375,549.5246" "4800.2625,665.1693")
(setq currobj (ssadd (entlast) currobj))
(command "_layer" "set" "nitride" "")
(setq coords (list 
(list 4800.2625 665.1693) 
(list 4800.5625 675.1693) 
(list 4800.5625 675.1693) 
(list 4800.5625 676.1693) 
(list 4874.585 675.4193) 
(list 4874.585 680.3623) 
(list 4800.5625 679.6123) 
(list 4800.5625 680.6123) 
(list 4800.5625 680.6123) 
(list 4800.2625 690.6123) 
(list 4799.7375 690.6123) 
(list 4799.4375 680.6123) 
(list 4799.4375 680.6123) 
(list 4799.4375 679.6123) 
(list 4725.415 680.3623) 
(list 4725.415 675.4193) 
(list 4799.4375 676.1693) 
(list 4799.4375 675.1693) 
(list 4799.4375 675.1693) 
(list 4799.7375 665.1693)))
(apply 'command (append '("pline") coords '("c")))
(setq currobj (ssadd (entlast) currobj))
(command "_layer" "set" "prebias" "")
(setq coords (list 
(list 4799.4375 665.1693) 
(list 4799.4375 676.1693) 
(list 4725.415 675.4193) 
(list 4725.415 680.3623) 
(list 4799.4375 679.6123) 
(list 4799.4375 690.6123) 
(list 4800.5625 690.6123) 
(list 4800.5625 679.6123) 
(list 4874.585 680.3623) 
(list 4874.585 675.4193) 
(list 4800.5625 676.1693) 
(list 4800.5625 665.1693)))
(apply 'command (append '("pline") coords '("c")))
(setq currobj (ssadd (entlast) currobj))
(command "_layer" "set" "nitride" "")
(command "_layer" "set" "fda1" "")
(setq coords (list 
(list 4800.5625 676.3123) 
(list 4874.585 675.5623) 
(list 4874.585 675.7393) 
(list 4800.5625 676.3893)))
(apply 'command (append '("pline") coords '("c")))
(setq currobj (ssadd (entlast) currobj))
(setq coords (list 
(list 4800.5625 676.5323) 
(list 4874.585 675.8823) 
(list 4874.585 676.0593) 
(list 4800.5625 676.6093)))
(apply 'command (append '("pline") coords '("c")))
(setq currobj (ssadd (entlast) currobj))
(setq coords (list 
(list 4800.5625 676.7523) 
(list 4874.585 676.2023) 
(list 4874.585 676.3793) 
(list 4800.5625 676.8293)))
(apply 'command (append '("pline") coords '("c")))
(setq currobj (ssadd (entlast) currobj))
(setq coords (list 
(list 4800.5625 676.9723) 
(list 4874.585 676.5223) 
(list 4874.585 676.6993) 
(list 4800.5625 677.0493)))
(apply 'command (append '("pline") coords '("c")))
(setq currobj (ssadd (entlast) currobj))
(setq coords (list 
(list 4800.5625 677.1923) 
(list 4874.585 676.8423) 
(list 4874.585 677.0193) 
(list 4800.5625 677.2693)))
(apply 'command (append '("pline") coords '("c")))
(setq currobj (ssadd (entlast) currobj))
(setq coords (list 
(list 4800.5625 677.4123) 
(list 4874.585 677.1623) 
(list 4874.585 677.3393) 
(list 4800.5625 677.4893)))
(apply 'command (append '("pline") coords '("c")))
(setq currobj (ssadd (entlast) currobj))
(setq coords (list 
(list 4800.5625 677.6323) 
(list 4874.585 677.4823) 
(list 4874.585 677.6593) 
(list 4800.5625 677.7093)))
(apply 'command (append '("pline") coords '("c")))
(setq currobj (ssadd (entlast) currobj))
(setq coords (list 
(list 4800.5625 677.8523) 
(list 4874.585 677.8023) 
(list 4874.585 677.9793) 
(list 4800.5625 677.9293)))
(apply 'command (append '("pline") coords '("c")))
(setq currobj (ssadd (entlast) currobj))
(setq coords (list 
(list 4800.5625 678.0723) 
(list 4874.585 678.1223) 
(list 4874.585 678.2993) 
(list 4800.5625 678.1493)))
(apply 'command (append '("pline") coords '("c")))
(setq currobj (ssadd (entlast) currobj))
(setq coords (list 
(list 4800.5625 678.2923) 
(list 4874.585 678.4423) 
(list 4874.585 678.6193) 
(list 4800.5625 678.3693)))
(apply 'command (append '("pline") coords '("c")))
(setq currobj (ssadd (entlast) currobj))
(setq coords (list 
(list 4800.5625 678.5123) 
(list 4874.585 678.7623) 
(list 4874.585 678.9393) 
(list 4800.5625 678.5893)))
(apply 'command (append '("pline") coords '("c")))
(setq currobj (ssadd (entlast) currobj))
(setq coords (list 
(list 4800.5625 678.7323) 
(list 4874.585 679.0823) 
(list 4874.585 679.2593) 
(list 4800.5625 678.8093)))
(apply 'command (append '("pline") coords '("c")))
(setq currobj (ssadd (entlast) currobj))
(setq coords (list 
(list 4800.5625 678.9523) 
(list 4874.585 679.4023) 
(list 4874.585 679.5793) 
(list 4800.5625 679.0293)))
(apply 'command (append '("pline") coords '("c")))
(setq currobj (ssadd (entlast) currobj))
(setq coords (list 
(list 4800.5625 679.1723) 
(list 4874.585 679.7223) 
(list 4874.585 679.8993) 
(list 4800.5625 679.2493)))
(apply 'command (append '("pline") coords '("c")))
(setq currobj (ssadd (entlast) currobj))
(setq coords (list 
(list 4800.5625 679.3923) 
(list 4874.585 680.0423) 
(list 4874.585 680.2193) 
(list 4800.5625 679.4693)))
(apply 'command (append '("pline") coords '("c")))
(setq currobj (ssadd (entlast) currobj))
(setq coords (list 
(list 4799.4375 679.4693) 
(list 4725.415 680.2193) 
(list 4725.415 680.0423) 
(list 4799.4375 679.3923)))
(apply 'command (append '("pline") coords '("c")))
(setq currobj (ssadd (entlast) currobj))
(setq coords (list 
(list 4799.4375 679.2493) 
(list 4725.415 679.8993) 
(list 4725.415 679.7223) 
(list 4799.4375 679.1723)))
(apply 'command (append '("pline") coords '("c")))
(setq currobj (ssadd (entlast) currobj))
(setq coords (list 
(list 4799.4375 679.0293) 
(list 4725.415 679.5793) 
(list 4725.415 679.4023) 
(list 4799.4375 678.9523)))
(apply 'command (append '("pline") coords '("c")))
(setq currobj (ssadd (entlast) currobj))
(setq coords (list 
(list 4799.4375 678.8093) 
(list 4725.415 679.2593) 
(list 4725.415 679.0823) 
(list 4799.4375 678.7323)))
(apply 'command (append '("pline") coords '("c")))
(setq currobj (ssadd (entlast) currobj))
(setq coords (list 
(list 4799.4375 678.5893) 
(list 4725.415 678.9393) 
(list 4725.415 678.7623) 
(list 4799.4375 678.5123)))
(apply 'command (append '("pline") coords '("c")))
(setq currobj (ssadd (entlast) currobj))
(setq coords (list 
(list 4799.4375 678.3693) 
(list 4725.415 678.6193) 
(list 4725.415 678.4423) 
(list 4799.4375 678.2923)))
(apply 'command (append '("pline") coords '("c")))
(setq currobj (ssadd (entlast) currobj))
(setq coords (list 
(list 4799.4375 678.1493) 
(list 4725.415 678.2993) 
(list 4725.415 678.1223) 
(list 4799.4375 678.0723)))
(apply 'command (append '("pline") coords '("c")))
(setq currobj (ssadd (entlast) currobj))
(setq coords (list 
(list 4799.4375 677.9293) 
(list 4725.415 677.9793) 
(list 4725.415 677.8023) 
(list 4799.4375 677.8523)))
(apply 'command (append '("pline") coords '("c")))
(setq currobj (ssadd (entlast) currobj))
(setq coords (list 
(list 4799.4375 677.7093) 
(list 4725.415 677.6593) 
(list 4725.415 677.4823) 
(list 4799.4375 677.6323)))
(apply 'command (append '("pline") coords '("c")))
(setq currobj (ssadd (entlast) currobj))
(setq coords (list 
(list 4799.4375 677.4893) 
(list 4725.415 677.3393) 
(list 4725.415 677.1623) 
(list 4799.4375 677.4123)))
(apply 'command (append '("pline") coords '("c")))
(setq currobj (ssadd (entlast) currobj))
(setq coords (list 
(list 4799.4375 677.2693) 
(list 4725.415 677.0193) 
(list 4725.415 676.8423) 
(list 4799.4375 677.1923)))
(apply 'command (append '("pline") coords '("c")))
(setq currobj (ssadd (entlast) currobj))
(setq coords (list 
(list 4799.4375 677.0493) 
(list 4725.415 676.6993) 
(list 4725.415 676.5223) 
(list 4799.4375 676.9723)))
(apply 'command (append '("pline") coords '("c")))
(setq currobj (ssadd (entlast) currobj))
(setq coords (list 
(list 4799.4375 676.8293) 
(list 4725.415 676.3793) 
(list 4725.415 676.2023) 
(list 4799.4375 676.7523)))
(apply 'command (append '("pline") coords '("c")))
(setq currobj (ssadd (entlast) currobj))
(setq coords (list 
(list 4799.4375 676.6093) 
(list 4725.415 676.0593) 
(list 4725.415 675.8823) 
(list 4799.4375 676.5323)))
(apply 'command (append '("pline") coords '("c")))
(setq currobj (ssadd (entlast) currobj))
(setq coords (list 
(list 4799.4375 676.3893) 
(list 4725.415 675.7393) 
(list 4725.415 675.5623) 
(list 4799.4375 676.3123)))
(apply 'command (append '("pline") coords '("c")))
(setq currobj (ssadd (entlast) currobj))
(command "_layer" "set" "nitride" "")
(command "_layer" "set" "text" "")
(command "_circle" "4799.0625,665.1693" "0.075")
(command "_circle" "4799.0625,665.4693" "0.075")
(command "_circle" "4799.0625,665.7693" "0.075")
(command "_circle" "4799.0625,666.0693" "0.075")
(command "_circle" "4799.0625,666.3693" "0.075")
(command "_circle" "4798.7625,665.1693" "0.075")
(command "_circle" "4798.7625,665.4693" "0.075")
(command "_circle" "4798.7625,665.7693" "0.075")
(command "_circle" "4798.7625,666.0693" "0.075")
(command "_circle" "4798.7625,666.3693" "0.075")
(command "_circle" "4798.4625,665.1693" "0.075")
(command "_circle" "4798.4625,665.4693" "0.075")
(command "_circle" "4798.4625,665.7693" "0.075")
(command "_circle" "4798.4625,666.0693" "0.075")
(command "_circle" "4798.4625,666.3693" "0.075")
(command "_circle" "4798.1625,665.1693" "0.075")
(command "_circle" "4798.1625,665.4693" "0.075")
(command "_circle" "4798.1625,665.7693" "0.075")
(command "_circle" "4798.1625,666.0693" "0.075")
(command "_circle" "4798.1625,666.3693" "0.075")
(command "_circle" "4797.8625,665.1693" "0.075")
(command "_circle" "4797.8625,665.4693" "0.075")
(command "_circle" "4797.8625,665.7693" "0.075")
(command "_circle" "4797.8625,666.0693" "0.075")
(command "_circle" "4797.8625,666.3693" "0.075")
(command "_layer" "set" "nitride" "")
(setq coords (list 
(list 4800.2625 690.6123) 
(list 4800.2625 806.257) 
(list 4799.7375 806.257) 
(list 4799.7375 690.6123)))
(apply 'command (append '("pline") coords '("c")))
(setq currobj (ssadd (entlast) currobj))
(command "_layer" "set" "prebias" "")
(command "_rectangle" "4799.7375,690.6123" "4800.2625,806.257")
(setq currobj (ssadd (entlast) currobj))
(command "_layer" "set" "nitride" "")
(setq coords (list 
(list 4800.2625 806.257) 
(list 4800.5625 816.257) 
(list 4800.5625 816.257) 
(list 4800.5625 817.257) 
(list 4874.585 816.507) 
(list 4874.585 821.45) 
(list 4800.5625 820.7) 
(list 4800.5625 821.7) 
(list 4800.5625 821.7) 
(list 4800.2625 831.7) 
(list 4799.7375 831.7) 
(list 4799.4375 821.7) 
(list 4799.4375 821.7) 
(list 4799.4375 820.7) 
(list 4725.415 821.45) 
(list 4725.415 816.507) 
(list 4799.4375 817.257) 
(list 4799.4375 816.257) 
(list 4799.4375 816.257) 
(list 4799.7375 806.257)))
(apply 'command (append '("pline") coords '("c")))
(setq currobj (ssadd (entlast) currobj))
(command "_layer" "set" "prebias" "")
(setq coords (list 
(list 4799.4375 806.257) 
(list 4799.4375 817.257) 
(list 4725.415 816.507) 
(list 4725.415 821.45) 
(list 4799.4375 820.7) 
(list 4799.4375 831.7) 
(list 4800.5625 831.7) 
(list 4800.5625 820.7) 
(list 4874.585 821.45) 
(list 4874.585 816.507) 
(list 4800.5625 817.257) 
(list 4800.5625 806.257)))
(apply 'command (append '("pline") coords '("c")))
(setq currobj (ssadd (entlast) currobj))
(command "_layer" "set" "nitride" "")
(command "_layer" "set" "fda1" "")
(setq coords (list 
(list 4800.5625 817.4) 
(list 4874.585 816.65) 
(list 4874.585 816.827) 
(list 4800.5625 817.477)))
(apply 'command (append '("pline") coords '("c")))
(setq currobj (ssadd (entlast) currobj))
(setq coords (list 
(list 4800.5625 817.62) 
(list 4874.585 816.97) 
(list 4874.585 817.147) 
(list 4800.5625 817.697)))
(apply 'command (append '("pline") coords '("c")))
(setq currobj (ssadd (entlast) currobj))
(setq coords (list 
(list 4800.5625 817.84) 
(list 4874.585 817.29) 
(list 4874.585 817.467) 
(list 4800.5625 817.917)))
(apply 'command (append '("pline") coords '("c")))
(setq currobj (ssadd (entlast) currobj))
(setq coords (list 
(list 4800.5625 818.06) 
(list 4874.585 817.61) 
(list 4874.585 817.787) 
(list 4800.5625 818.137)))
(apply 'command (append '("pline") coords '("c")))
(setq currobj (ssadd (entlast) currobj))
(setq coords (list 
(list 4800.5625 818.28) 
(list 4874.585 817.93) 
(list 4874.585 818.107) 
(list 4800.5625 818.357)))
(apply 'command (append '("pline") coords '("c")))
(setq currobj (ssadd (entlast) currobj))
(setq coords (list 
(list 4800.5625 818.5) 
(list 4874.585 818.25) 
(list 4874.585 818.427) 
(list 4800.5625 818.577)))
(apply 'command (append '("pline") coords '("c")))
(setq currobj (ssadd (entlast) currobj))
(setq coords (list 
(list 4800.5625 818.72) 
(list 4874.585 818.57) 
(list 4874.585 818.747) 
(list 4800.5625 818.797)))
(apply 'command (append '("pline") coords '("c")))
(setq currobj (ssadd (entlast) currobj))
(setq coords (list 
(list 4800.5625 818.94) 
(list 4874.585 818.89) 
(list 4874.585 819.067) 
(list 4800.5625 819.017)))
(apply 'command (append '("pline") coords '("c")))
(setq currobj (ssadd (entlast) currobj))
(setq coords (list 
(list 4800.5625 819.16) 
(list 4874.585 819.21) 
(list 4874.585 819.387) 
(list 4800.5625 819.237)))
(apply 'command (append '("pline") coords '("c")))
(setq currobj (ssadd (entlast) currobj))
(setq coords (list 
(list 4800.5625 819.38) 
(list 4874.585 819.53) 
(list 4874.585 819.707) 
(list 4800.5625 819.457)))
(apply 'command (append '("pline") coords '("c")))
(setq currobj (ssadd (entlast) currobj))
(setq coords (list 
(list 4800.5625 819.6) 
(list 4874.585 819.85) 
(list 4874.585 820.027) 
(list 4800.5625 819.677)))
(apply 'command (append '("pline") coords '("c")))
(setq currobj (ssadd (entlast) currobj))
(setq coords (list 
(list 4800.5625 819.82) 
(list 4874.585 820.17) 
(list 4874.585 820.347) 
(list 4800.5625 819.897)))
(apply 'command (append '("pline") coords '("c")))
(setq currobj (ssadd (entlast) currobj))
(setq coords (list 
(list 4800.5625 820.04) 
(list 4874.585 820.49) 
(list 4874.585 820.667) 
(list 4800.5625 820.117)))
(apply 'command (append '("pline") coords '("c")))
(setq currobj (ssadd (entlast) currobj))
(setq coords (list 
(list 4800.5625 820.26) 
(list 4874.585 820.81) 
(list 4874.585 820.987) 
(list 4800.5625 820.337)))
(apply 'command (append '("pline") coords '("c")))
(setq currobj (ssadd (entlast) currobj))
(setq coords (list 
(list 4800.5625 820.48) 
(list 4874.585 821.13) 
(list 4874.585 821.307) 
(list 4800.5625 820.557)))
(apply 'command (append '("pline") coords '("c")))
(setq currobj (ssadd (entlast) currobj))
(setq coords (list 
(list 4799.4375 820.557) 
(list 4725.415 821.307) 
(list 4725.415 821.13) 
(list 4799.4375 820.48)))
(apply 'command (append '("pline") coords '("c")))
(setq currobj (ssadd (entlast) currobj))
(setq coords (list 
(list 4799.4375 820.337) 
(list 4725.415 820.987) 
(list 4725.415 820.81) 
(list 4799.4375 820.26)))
(apply 'command (append '("pline") coords '("c")))
(setq currobj (ssadd (entlast) currobj))
(setq coords (list 
(list 4799.4375 820.117) 
(list 4725.415 820.667) 
(list 4725.415 820.49) 
(list 4799.4375 820.04)))
(apply 'command (append '("pline") coords '("c")))
(setq currobj (ssadd (entlast) currobj))
(setq coords (list 
(list 4799.4375 819.897) 
(list 4725.415 820.347) 
(list 4725.415 820.17) 
(list 4799.4375 819.82)))
(apply 'command (append '("pline") coords '("c")))
(setq currobj (ssadd (entlast) currobj))
(setq coords (list 
(list 4799.4375 819.677) 
(list 4725.415 820.027) 
(list 4725.415 819.85) 
(list 4799.4375 819.6)))
(apply 'command (append '("pline") coords '("c")))
(setq currobj (ssadd (entlast) currobj))
(setq coords (list 
(list 4799.4375 819.457) 
(list 4725.415 819.707) 
(list 4725.415 819.53) 
(list 4799.4375 819.38)))
(apply 'command (append '("pline") coords '("c")))
(setq currobj (ssadd (entlast) currobj))
(setq coords (list 
(list 4799.4375 819.237) 
(list 4725.415 819.387) 
(list 4725.415 819.21) 
(list 4799.4375 819.16)))
(apply 'command (append '("pline") coords '("c")))
(setq currobj (ssadd (entlast) currobj))
(setq coords (list 
(list 4799.4375 819.017) 
(list 4725.415 819.067) 
(list 4725.415 818.89) 
(list 4799.4375 818.94)))
(apply 'command (append '("pline") coords '("c")))
(setq currobj (ssadd (entlast) currobj))
(setq coords (list 
(list 4799.4375 818.797) 
(list 4725.415 818.747) 
(list 4725.415 818.57) 
(list 4799.4375 818.72)))
(apply 'command (append '("pline") coords '("c")))
(setq currobj (ssadd (entlast) currobj))
(setq coords (list 
(list 4799.4375 818.577) 
(list 4725.415 818.427) 
(list 4725.415 818.25) 
(list 4799.4375 818.5)))
(apply 'command (append '("pline") coords '("c")))
(setq currobj (ssadd (entlast) currobj))
(setq coords (list 
(list 4799.4375 818.357) 
(list 4725.415 818.107) 
(list 4725.415 817.93) 
(list 4799.4375 818.28)))
(apply 'command (append '("pline") coords '("c")))
(setq currobj (ssadd (entlast) currobj))
(setq coords (list 
(list 4799.4375 818.137) 
(list 4725.415 817.787) 
(list 4725.415 817.61) 
(list 4799.4375 818.06)))
(apply 'command (append '("pline") coords '("c")))
(setq currobj (ssadd (entlast) currobj))
(setq coords (list 
(list 4799.4375 817.917) 
(list 4725.415 817.467) 
(list 4725.415 817.29) 
(list 4799.4375 817.84)))
(apply 'command (append '("pline") coords '("c")))
(setq currobj (ssadd (entlast) currobj))
(setq coords (list 
(list 4799.4375 817.697) 
(list 4725.415 817.147) 
(list 4725.415 816.97) 
(list 4799.4375 817.62)))
(apply 'command (append '("pline") coords '("c")))
(setq currobj (ssadd (entlast) currobj))
(setq coords (list 
(list 4799.4375 817.477) 
(list 4725.415 816.827) 
(list 4725.415 816.65) 
(list 4799.4375 817.4)))
(apply 'command (append '("pline") coords '("c")))
(setq currobj (ssadd (entlast) currobj))
(command "_layer" "set" "nitride" "")
(command "_layer" "set" "text" "")
(command "_circle" "4799.0625,806.257" "0.075")
(command "_circle" "4799.0625,806.557" "0.075")
(command "_circle" "4799.0625,806.857" "0.075")
(command "_circle" "4799.0625,807.157" "0.075")
(command "_circle" "4799.0625,807.457" "0.075")
(command "_circle" "4798.7625,806.257" "0.075")
(command "_circle" "4798.7625,806.557" "0.075")
(command "_circle" "4798.7625,806.857" "0.075")
(command "_circle" "4798.7625,807.157" "0.075")
(command "_circle" "4798.7625,807.457" "0.075")
(command "_circle" "4798.4625,806.257" "0.075")
(command "_circle" "4798.4625,806.557" "0.075")
(command "_circle" "4798.4625,806.857" "0.075")
(command "_circle" "4798.4625,807.157" "0.075")
(command "_circle" "4798.4625,807.457" "0.075")
(command "_circle" "4798.1625,806.257" "0.075")
(command "_circle" "4798.1625,806.557" "0.075")
(command "_circle" "4798.1625,806.857" "0.075")
(command "_circle" "4798.1625,807.157" "0.075")
(command "_circle" "4798.1625,807.457" "0.075")
(command "_circle" "4797.8625,806.257" "0.075")
(command "_circle" "4797.8625,806.557" "0.075")
(command "_circle" "4797.8625,806.857" "0.075")
(command "_circle" "4797.8625,807.157" "0.075")
(command "_circle" "4797.8625,807.457" "0.075")
(command "_layer" "set" "nitride" "")
(setq coords (list 
(list 4800.2625 831.7) 
(list 4800.2625 836.7) 
(list 4799.7375 836.7) 
(list 4799.7375 831.7)))
(apply 'command (append '("pline") coords '("c")))
(setq currobj (ssadd (entlast) currobj))
(command "_layer" "set" "prebias" "")
(command "_rectangle" "4799.7375,831.7" "4800.2625,836.7")
(setq currobj (ssadd (entlast) currobj))
(command "_layer" "set" "nitride" "")
(setq cooledsinglenanobeam15 currobj)
(setq currobj nil)
(setq currobj (ssadd))
; DRAWING PHOTONIC CRYSTAL
(command "_layer" "set" "negYjunc" "")
(setq coords (list 
(list 4800.135 866.7) 
(list 4800 851.7) 
(list 4800 866.7)))
(apply 'command (append '("pline") coords '("c")))
(setq currobj (ssadd (entlast) currobj))
(setq coords (list 
(list 4800.2625 836.7) 
(list 4800.415 866.7) 
(list 4801.116 866.7) 
(list 4801.116 836.7)))
(apply 'command (append '("pline") coords '("c")))
(setq currobj (ssadd (entlast) currobj))
(setq coords (list 
(list 4799.865 866.7) 
(list 4800 851.7) 
(list 4800 866.7)))
(apply 'command (append '("pline") coords '("c")))
(setq currobj (ssadd (entlast) currobj))
(setq coords (list 
(list 4799.7375 836.7) 
(list 4799.585 866.7) 
(list 4798.884 866.7) 
(list 4798.884 836.7)))
(apply 'command (append '("pline") coords '("c")))
(setq currobj (ssadd (entlast) currobj))
(command "_layer" "set" "nitride" "")
(setq yjunction15 currobj)
(setq currobj nil)
(setq currobj (ssadd))
(setq tap15 nil)
(setq tap15 (ssadd))
(command "_layer" "set" "phc" "")
(setq coords (list 
(list 4800 866.7) 
(list 4800.135 866.7) 
(list 4800.135 866.7103) 
(list 4800.135 866.7206) 
(list 4800.135 866.7308) 
(list 4800.135 866.7411) 
(list 4800.135 866.7514) 
(list 4800.135 866.7617) 
(list 4800.135 866.7719) 
(list 4800.135 866.7822) 
(list 4800.135 866.7925) 
(list 4800.135 866.8028) 
(list 4800.135 866.8131) 
(list 4800.135 866.8233) 
(list 4800.135 866.8336) 
(list 4800.135 866.8439) 
(list 4800.135 866.8542) 
(list 4800.135 866.8644) 
(list 4800.135 866.8747) 
(list 4800.135 866.885) 
(list 4800.135 866.8953) 
(list 4800.135 866.9056) 
(list 4800.135 866.9158) 
(list 4800.135 866.9261) 
(list 4800.135 866.9364) 
(list 4800.135 866.9467) 
(list 4800.135 866.9569) 
(list 4800.135 866.9672) 
(list 4800.135 866.9775) 
(list 4800.135 866.9878) 
(list 4800.135 866.9981) 
(list 4800.135 867.0083) 
(list 4800.135 867.0186) 
(list 4800.135 867.0289) 
(list 4800.135 867.0392) 
(list 4800.135 867.0494) 
(list 4800.135 867.0597) 
(list 4800.135 867.07) 
(list 4800 867.07)))
(apply 'command (append '("pline") coords '("c")))
(setq tap15 (ssadd (entlast) tap15))
(command "_mirror" (entlast) "" "4800,900" "4800,901" "No")
(setq tap15 (ssadd (entlast) tap15))
(setq coords (list 
(list 4800.4245 866.7) 
(list 4800.415 866.7) 
(list 4800.4153 866.7103) 
(list 4800.4155 866.7206) 
(list 4800.4157 866.7308) 
(list 4800.4158 866.7411) 
(list 4800.4159 866.7514) 
(list 4800.4159 866.7617) 
(list 4800.4157 866.7719) 
(list 4800.4155 866.7822) 
(list 4800.4152 866.7925) 
(list 4800.4148 866.8028) 
(list 4800.4143 866.8131) 
(list 4800.4138 866.8233) 
(list 4800.4132 866.8336) 
(list 4800.4127 866.8439) 
(list 4800.4121 866.8542) 
(list 4800.4117 866.8644) 
(list 4800.4113 866.8747) 
(list 4800.411 866.885) 
(list 4800.4108 866.8953) 
(list 4800.4108 866.9056) 
(list 4800.411 866.9158) 
(list 4800.4113 866.9261) 
(list 4800.4119 866.9364) 
(list 4800.4126 866.9467) 
(list 4800.4134 866.9569) 
(list 4800.4144 866.9672) 
(list 4800.4155 866.9775) 
(list 4800.4168 866.9878) 
(list 4800.418 866.9981) 
(list 4800.4193 867.0083) 
(list 4800.4205 867.0186) 
(list 4800.4216 867.0289) 
(list 4800.4227 867.0392) 
(list 4800.4235 867.0494) 
(list 4800.4241 867.0597) 
(list 4800.4245 867.07) 
(list 4800.4245 867.07)))
(apply 'command (append '("pline") coords '("c")))
(setq tap15 (ssadd (entlast) tap15))
(command "_mirror" (entlast) "" "4800,900" "4800,901" "No")
(setq tap15 (ssadd (entlast) tap15))
(setq coords (list 
(list 4801.116 866.7) 
(list 4800.4245 866.7) 
(list 4800.4245 866.7103) 
(list 4800.4245 866.7206) 
(list 4800.4245 866.7308) 
(list 4800.4245 866.7411) 
(list 4800.4245 866.7514) 
(list 4800.4245 866.7617) 
(list 4800.4245 866.7719) 
(list 4800.4245 866.7822) 
(list 4800.4245 866.7925) 
(list 4800.4245 866.8028) 
(list 4800.4245 866.8131) 
(list 4800.4245 866.8233) 
(list 4800.4245 866.8336) 
(list 4800.4245 866.8439) 
(list 4800.4245 866.8542) 
(list 4800.4245 866.8644) 
(list 4800.4245 866.8747) 
(list 4800.4245 866.885) 
(list 4800.4245 866.8953) 
(list 4800.4245 866.9056) 
(list 4800.4245 866.9158) 
(list 4800.4245 866.9261) 
(list 4800.4245 866.9364) 
(list 4800.4245 866.9467) 
(list 4800.4245 866.9569) 
(list 4800.4245 866.9672) 
(list 4800.4245 866.9775) 
(list 4800.4245 866.9878) 
(list 4800.4245 866.9981) 
(list 4800.4245 867.0083) 
(list 4800.4245 867.0186) 
(list 4800.4245 867.0289) 
(list 4800.4245 867.0392) 
(list 4800.4245 867.0494) 
(list 4800.4245 867.0597) 
(list 4800.4245 867.07) 
(list 4801.116 867.07)))
(apply 'command (append '("pline") coords '("c")))
(setq tap15 (ssadd (entlast) tap15))
(command "_mirror" (entlast) "" "4800,900" "4800,901" "No")
(setq tap15 (ssadd (entlast) tap15))
(setq coords (list 
(list 4800 867.07) 
(list 4800.135 867.07) 
(list 4800.135 867.0803) 
(list 4800.135 867.0906) 
(list 4800.135 867.1008) 
(list 4800.135 867.1111) 
(list 4800.135 867.1214) 
(list 4800.135 867.1317) 
(list 4800.135 867.1419) 
(list 4800.135 867.1522) 
(list 4800.135 867.1625) 
(list 4800.135 867.1728) 
(list 4800.135 867.1831) 
(list 4800.135 867.1933) 
(list 4800.135 867.2036) 
(list 4800.135 867.2139) 
(list 4800.135 867.2242) 
(list 4800.135 867.2344) 
(list 4800.135 867.2447) 
(list 4800.135 867.255) 
(list 4800.135 867.2653) 
(list 4800.135 867.2756) 
(list 4800.135 867.2858) 
(list 4800.135 867.2961) 
(list 4800.135 867.3064) 
(list 4800.135 867.3167) 
(list 4800.135 867.3269) 
(list 4800.135 867.3372) 
(list 4800.135 867.3475) 
(list 4800.135 867.3578) 
(list 4800.135 867.3681) 
(list 4800.135 867.3783) 
(list 4800.135 867.3886) 
(list 4800.135 867.3989) 
(list 4800.135 867.4092) 
(list 4800.135 867.4194) 
(list 4800.135 867.4297) 
(list 4800.135 867.44) 
(list 4800 867.44)))
(apply 'command (append '("pline") coords '("c")))
(setq tap15 (ssadd (entlast) tap15))
(command "_mirror" (entlast) "" "4800,900" "4800,901" "No")
(setq tap15 (ssadd (entlast) tap15))
(setq coords (list 
(list 4800.4341 867.07) 
(list 4800.4245 867.07) 
(list 4800.4247 867.0803) 
(list 4800.4245 867.0906) 
(list 4800.4241 867.1008) 
(list 4800.4233 867.1111) 
(list 4800.4223 867.1214) 
(list 4800.421 867.1317) 
(list 4800.4195 867.1419) 
(list 4800.4178 867.1522) 
(list 4800.4159 867.1625) 
(list 4800.414 867.1728) 
(list 4800.412 867.1831) 
(list 4800.4101 867.1933) 
(list 4800.4083 867.2036) 
(list 4800.4067 867.2139) 
(list 4800.4052 867.2242) 
(list 4800.4041 867.2344) 
(list 4800.4033 867.2447) 
(list 4800.4029 867.255) 
(list 4800.4029 867.2653) 
(list 4800.4033 867.2756) 
(list 4800.4041 867.2858) 
(list 4800.4053 867.2961) 
(list 4800.4069 867.3064) 
(list 4800.4089 867.3167) 
(list 4800.4111 867.3269) 
(list 4800.4136 867.3372) 
(list 4800.4163 867.3475) 
(list 4800.419 867.3578) 
(list 4800.4218 867.3681) 
(list 4800.4244 867.3783) 
(list 4800.4269 867.3886) 
(list 4800.4291 867.3989) 
(list 4800.431 867.4092) 
(list 4800.4325 867.4194) 
(list 4800.4335 867.4297) 
(list 4800.4341 867.44) 
(list 4800.4341 867.44)))
(apply 'command (append '("pline") coords '("c")))
(setq tap15 (ssadd (entlast) tap15))
(command "_mirror" (entlast) "" "4800,900" "4800,901" "No")
(setq tap15 (ssadd (entlast) tap15))
(setq coords (list 
(list 4801.116 867.07) 
(list 4800.4341 867.07) 
(list 4800.4341 867.0803) 
(list 4800.4341 867.0906) 
(list 4800.4341 867.1008) 
(list 4800.4341 867.1111) 
(list 4800.4341 867.1214) 
(list 4800.4341 867.1317) 
(list 4800.4341 867.1419) 
(list 4800.4341 867.1522) 
(list 4800.4341 867.1625) 
(list 4800.4341 867.1728) 
(list 4800.4341 867.1831) 
(list 4800.4341 867.1933) 
(list 4800.4341 867.2036) 
(list 4800.4341 867.2139) 
(list 4800.4341 867.2242) 
(list 4800.4341 867.2344) 
(list 4800.4341 867.2447) 
(list 4800.4341 867.255) 
(list 4800.4341 867.2653) 
(list 4800.4341 867.2756) 
(list 4800.4341 867.2858) 
(list 4800.4341 867.2961) 
(list 4800.4341 867.3064) 
(list 4800.4341 867.3167) 
(list 4800.4341 867.3269) 
(list 4800.4341 867.3372) 
(list 4800.4341 867.3475) 
(list 4800.4341 867.3578) 
(list 4800.4341 867.3681) 
(list 4800.4341 867.3783) 
(list 4800.4341 867.3886) 
(list 4800.4341 867.3989) 
(list 4800.4341 867.4092) 
(list 4800.4341 867.4194) 
(list 4800.4341 867.4297) 
(list 4800.4341 867.44) 
(list 4801.116 867.44)))
(apply 'command (append '("pline") coords '("c")))
(setq tap15 (ssadd (entlast) tap15))
(command "_mirror" (entlast) "" "4800,900" "4800,901" "No")
(setq tap15 (ssadd (entlast) tap15))
(setq coords (list 
(list 4800 867.44) 
(list 4800.135 867.44) 
(list 4800.135 867.4503) 
(list 4800.135 867.4606) 
(list 4800.135 867.4708) 
(list 4800.135 867.4811) 
(list 4800.135 867.4914) 
(list 4800.135 867.5017) 
(list 4800.135 867.5119) 
(list 4800.135 867.5222) 
(list 4800.135 867.5325) 
(list 4800.135 867.5428) 
(list 4800.135 867.5531) 
(list 4800.135 867.5633) 
(list 4800.135 867.5736) 
(list 4800.135 867.5839) 
(list 4800.135 867.5942) 
(list 4800.135 867.6044) 
(list 4800.135 867.6147) 
(list 4800.135 867.625) 
(list 4800.135 867.6353) 
(list 4800.135 867.6456) 
(list 4800.135 867.6558) 
(list 4800.135 867.6661) 
(list 4800.135 867.6764) 
(list 4800.135 867.6867) 
(list 4800.135 867.6969) 
(list 4800.135 867.7072) 
(list 4800.135 867.7175) 
(list 4800.135 867.7278) 
(list 4800.135 867.7381) 
(list 4800.135 867.7483) 
(list 4800.135 867.7586) 
(list 4800.135 867.7689) 
(list 4800.135 867.7792) 
(list 4800.135 867.7894) 
(list 4800.135 867.7997) 
(list 4800.135 867.81) 
(list 4800 867.81)))
(apply 'command (append '("pline") coords '("c")))
(setq tap15 (ssadd (entlast) tap15))
(command "_mirror" (entlast) "" "4800,900" "4800,901" "No")
(setq tap15 (ssadd (entlast) tap15))
(setq coords (list 
(list 4800.4436 867.44) 
(list 4800.4341 867.44) 
(list 4800.4341 867.4503) 
(list 4800.4335 867.4606) 
(list 4800.4324 867.4708) 
(list 4800.4308 867.4811) 
(list 4800.4287 867.4914) 
(list 4800.4261 867.5017) 
(list 4800.4232 867.5119) 
(list 4800.42 867.5222) 
(list 4800.4167 867.5325) 
(list 4800.4132 867.5428) 
(list 4800.4098 867.5531) 
(list 4800.4064 867.5633) 
(list 4800.4034 867.5736) 
(list 4800.4006 867.5839) 
(list 4800.3984 867.5942) 
(list 4800.3966 867.6044) 
(list 4800.3954 867.6147) 
(list 4800.3948 867.625) 
(list 4800.3949 867.6353) 
(list 4800.3957 867.6456) 
(list 4800.3972 867.6558) 
(list 4800.3993 867.6661) 
(list 4800.402 867.6764) 
(list 4800.4052 867.6867) 
(list 4800.4089 867.6969) 
(list 4800.4128 867.7072) 
(list 4800.417 867.7175) 
(list 4800.4213 867.7278) 
(list 4800.4255 867.7381) 
(list 4800.4295 867.7483) 
(list 4800.4333 867.7586) 
(list 4800.4366 867.7689) 
(list 4800.4394 867.7792) 
(list 4800.4415 867.7894) 
(list 4800.4429 867.7997) 
(list 4800.4436 867.81) 
(list 4800.4436 867.81)))
(apply 'command (append '("pline") coords '("c")))
(setq tap15 (ssadd (entlast) tap15))
(command "_mirror" (entlast) "" "4800,900" "4800,901" "No")
(setq tap15 (ssadd (entlast) tap15))
(setq coords (list 
(list 4801.116 867.44) 
(list 4800.4436 867.44) 
(list 4800.4436 867.4503) 
(list 4800.4436 867.4606) 
(list 4800.4436 867.4708) 
(list 4800.4436 867.4811) 
(list 4800.4436 867.4914) 
(list 4800.4436 867.5017) 
(list 4800.4436 867.5119) 
(list 4800.4436 867.5222) 
(list 4800.4436 867.5325) 
(list 4800.4436 867.5428) 
(list 4800.4436 867.5531) 
(list 4800.4436 867.5633) 
(list 4800.4436 867.5736) 
(list 4800.4436 867.5839) 
(list 4800.4436 867.5942) 
(list 4800.4436 867.6044) 
(list 4800.4436 867.6147) 
(list 4800.4436 867.625) 
(list 4800.4436 867.6353) 
(list 4800.4436 867.6456) 
(list 4800.4436 867.6558) 
(list 4800.4436 867.6661) 
(list 4800.4436 867.6764) 
(list 4800.4436 867.6867) 
(list 4800.4436 867.6969) 
(list 4800.4436 867.7072) 
(list 4800.4436 867.7175) 
(list 4800.4436 867.7278) 
(list 4800.4436 867.7381) 
(list 4800.4436 867.7483) 
(list 4800.4436 867.7586) 
(list 4800.4436 867.7689) 
(list 4800.4436 867.7792) 
(list 4800.4436 867.7894) 
(list 4800.4436 867.7997) 
(list 4800.4436 867.81) 
(list 4801.116 867.81)))
(apply 'command (append '("pline") coords '("c")))
(setq tap15 (ssadd (entlast) tap15))
(command "_mirror" (entlast) "" "4800,900" "4800,901" "No")
(setq tap15 (ssadd (entlast) tap15))
(setq coords (list 
(list 4800 867.81) 
(list 4800.135 867.81) 
(list 4800.135 867.8203) 
(list 4800.135 867.8306) 
(list 4800.135 867.8408) 
(list 4800.135 867.8511) 
(list 4800.135 867.8614) 
(list 4800.135 867.8717) 
(list 4800.135 867.8819) 
(list 4800.135 867.8922) 
(list 4800.135 867.9025) 
(list 4800.135 867.9128) 
(list 4800.135 867.9231) 
(list 4800.135 867.9333) 
(list 4800.135 867.9436) 
(list 4800.135 867.9539) 
(list 4800.135 867.9642) 
(list 4800.135 867.9744) 
(list 4800.135 867.9847) 
(list 4800.135 867.995) 
(list 4800.135 868.0053) 
(list 4800.135 868.0156) 
(list 4800.135 868.0258) 
(list 4800.135 868.0361) 
(list 4800.135 868.0464) 
(list 4800.135 868.0567) 
(list 4800.135 868.0669) 
(list 4800.135 868.0772) 
(list 4800.135 868.0875) 
(list 4800.135 868.0978) 
(list 4800.135 868.1081) 
(list 4800.135 868.1183) 
(list 4800.135 868.1286) 
(list 4800.135 868.1389) 
(list 4800.135 868.1492) 
(list 4800.135 868.1594) 
(list 4800.135 868.1697) 
(list 4800.135 868.18) 
(list 4800 868.18)))
(apply 'command (append '("pline") coords '("c")))
(setq tap15 (ssadd (entlast) tap15))
(command "_mirror" (entlast) "" "4800,900" "4800,901" "No")
(setq tap15 (ssadd (entlast) tap15))
(setq coords (list 
(list 4800.4531 867.81) 
(list 4800.4436 867.81) 
(list 4800.4435 867.8203) 
(list 4800.4425 867.8306) 
(list 4800.4408 867.8408) 
(list 4800.4383 867.8511) 
(list 4800.4351 867.8614) 
(list 4800.4313 867.8717) 
(list 4800.427 867.8819) 
(list 4800.4223 867.8922) 
(list 4800.4174 867.9025) 
(list 4800.4124 867.9128) 
(list 4800.4075 867.9231) 
(list 4800.4028 867.9333) 
(list 4800.3985 867.9436) 
(list 4800.3946 867.9539) 
(list 4800.3915 867.9642) 
(list 4800.389 867.9744) 
(list 4800.3875 867.9847) 
(list 4800.3868 867.995) 
(list 4800.387 868.0053) 
(list 4800.3882 868.0156) 
(list 4800.3903 868.0258) 
(list 4800.3933 868.0361) 
(list 4800.3971 868.0464) 
(list 4800.4016 868.0567) 
(list 4800.4066 868.0669) 
(list 4800.412 868.0772) 
(list 4800.4177 868.0875) 
(list 4800.4235 868.0978) 
(list 4800.4292 868.1081) 
(list 4800.4347 868.1183) 
(list 4800.4397 868.1286) 
(list 4800.4441 868.1389) 
(list 4800.4477 868.1492) 
(list 4800.4505 868.1594) 
(list 4800.4523 868.1697) 
(list 4800.4531 868.18) 
(list 4800.4531 868.18)))
(apply 'command (append '("pline") coords '("c")))
(setq tap15 (ssadd (entlast) tap15))
(command "_mirror" (entlast) "" "4800,900" "4800,901" "No")
(setq tap15 (ssadd (entlast) tap15))
(setq coords (list 
(list 4801.116 867.81) 
(list 4800.4531 867.81) 
(list 4800.4531 867.8203) 
(list 4800.4531 867.8306) 
(list 4800.4531 867.8408) 
(list 4800.4531 867.8511) 
(list 4800.4531 867.8614) 
(list 4800.4531 867.8717) 
(list 4800.4531 867.8819) 
(list 4800.4531 867.8922) 
(list 4800.4531 867.9025) 
(list 4800.4531 867.9128) 
(list 4800.4531 867.9231) 
(list 4800.4531 867.9333) 
(list 4800.4531 867.9436) 
(list 4800.4531 867.9539) 
(list 4800.4531 867.9642) 
(list 4800.4531 867.9744) 
(list 4800.4531 867.9847) 
(list 4800.4531 867.995) 
(list 4800.4531 868.0053) 
(list 4800.4531 868.0156) 
(list 4800.4531 868.0258) 
(list 4800.4531 868.0361) 
(list 4800.4531 868.0464) 
(list 4800.4531 868.0567) 
(list 4800.4531 868.0669) 
(list 4800.4531 868.0772) 
(list 4800.4531 868.0875) 
(list 4800.4531 868.0978) 
(list 4800.4531 868.1081) 
(list 4800.4531 868.1183) 
(list 4800.4531 868.1286) 
(list 4800.4531 868.1389) 
(list 4800.4531 868.1492) 
(list 4800.4531 868.1594) 
(list 4800.4531 868.1697) 
(list 4800.4531 868.18) 
(list 4801.116 868.18)))
(apply 'command (append '("pline") coords '("c")))
(setq tap15 (ssadd (entlast) tap15))
(command "_mirror" (entlast) "" "4800,900" "4800,901" "No")
(setq tap15 (ssadd (entlast) tap15))
(setq coords (list 
(list 4800 868.18) 
(list 4800.135 868.18) 
(list 4800.135 868.1903) 
(list 4800.135 868.2006) 
(list 4800.135 868.2108) 
(list 4800.135 868.2211) 
(list 4800.135 868.2314) 
(list 4800.135 868.2417) 
(list 4800.135 868.2519) 
(list 4800.135 868.2622) 
(list 4800.135 868.2725) 
(list 4800.135 868.2828) 
(list 4800.135 868.2931) 
(list 4800.135 868.3033) 
(list 4800.135 868.3136) 
(list 4800.135 868.3239) 
(list 4800.135 868.3342) 
(list 4800.135 868.3444) 
(list 4800.135 868.3547) 
(list 4800.135 868.365) 
(list 4800.135 868.3753) 
(list 4800.135 868.3856) 
(list 4800.135 868.3958) 
(list 4800.135 868.4061) 
(list 4800.135 868.4164) 
(list 4800.135 868.4267) 
(list 4800.135 868.4369) 
(list 4800.135 868.4472) 
(list 4800.135 868.4575) 
(list 4800.135 868.4678) 
(list 4800.135 868.4781) 
(list 4800.135 868.4883) 
(list 4800.135 868.4986) 
(list 4800.135 868.5089) 
(list 4800.135 868.5192) 
(list 4800.135 868.5294) 
(list 4800.135 868.5397) 
(list 4800.135 868.55) 
(list 4800 868.55)))
(apply 'command (append '("pline") coords '("c")))
(setq tap15 (ssadd (entlast) tap15))
(command "_mirror" (entlast) "" "4800,900" "4800,901" "No")
(setq tap15 (ssadd (entlast) tap15))
(setq coords (list 
(list 4800.4627 868.18) 
(list 4800.4531 868.18) 
(list 4800.4529 868.1903) 
(list 4800.4515 868.2006) 
(list 4800.4491 868.2108) 
(list 4800.4457 868.2211) 
(list 4800.4414 868.2314) 
(list 4800.4364 868.2417) 
(list 4800.4307 868.2519) 
(list 4800.4245 868.2622) 
(list 4800.4181 868.2725) 
(list 4800.4116 868.2828) 
(list 4800.4052 868.2931) 
(list 4800.3991 868.3033) 
(list 4800.3935 868.3136) 
(list 4800.3886 868.3239) 
(list 4800.3846 868.3342) 
(list 4800.3815 868.3444) 
(list 4800.3795 868.3547) 
(list 4800.3787 868.365) 
(list 4800.3791 868.3753) 
(list 4800.3807 868.3856) 
(list 4800.3834 868.3958) 
(list 4800.3873 868.4061) 
(list 4800.3922 868.4164) 
(list 4800.3979 868.4267) 
(list 4800.4043 868.4369) 
(list 4800.4112 868.4472) 
(list 4800.4185 868.4575) 
(list 4800.4258 868.4678) 
(list 4800.433 868.4781) 
(list 4800.4398 868.4883) 
(list 4800.4461 868.4986) 
(list 4800.4515 868.5089) 
(list 4800.4561 868.5192) 
(list 4800.4595 868.5294) 
(list 4800.4617 868.5397) 
(list 4800.4627 868.55) 
(list 4800.4627 868.55)))
(apply 'command (append '("pline") coords '("c")))
(setq tap15 (ssadd (entlast) tap15))
(command "_mirror" (entlast) "" "4800,900" "4800,901" "No")
(setq tap15 (ssadd (entlast) tap15))
(setq coords (list 
(list 4801.116 868.18) 
(list 4800.4627 868.18) 
(list 4800.4627 868.1903) 
(list 4800.4627 868.2006) 
(list 4800.4627 868.2108) 
(list 4800.4627 868.2211) 
(list 4800.4627 868.2314) 
(list 4800.4627 868.2417) 
(list 4800.4627 868.2519) 
(list 4800.4627 868.2622) 
(list 4800.4627 868.2725) 
(list 4800.4627 868.2828) 
(list 4800.4627 868.2931) 
(list 4800.4627 868.3033) 
(list 4800.4627 868.3136) 
(list 4800.4627 868.3239) 
(list 4800.4627 868.3342) 
(list 4800.4627 868.3444) 
(list 4800.4627 868.3547) 
(list 4800.4627 868.365) 
(list 4800.4627 868.3753) 
(list 4800.4627 868.3856) 
(list 4800.4627 868.3958) 
(list 4800.4627 868.4061) 
(list 4800.4627 868.4164) 
(list 4800.4627 868.4267) 
(list 4800.4627 868.4369) 
(list 4800.4627 868.4472) 
(list 4800.4627 868.4575) 
(list 4800.4627 868.4678) 
(list 4800.4627 868.4781) 
(list 4800.4627 868.4883) 
(list 4800.4627 868.4986) 
(list 4800.4627 868.5089) 
(list 4800.4627 868.5192) 
(list 4800.4627 868.5294) 
(list 4800.4627 868.5397) 
(list 4800.4627 868.55) 
(list 4801.116 868.55)))
(apply 'command (append '("pline") coords '("c")))
(setq tap15 (ssadd (entlast) tap15))
(command "_mirror" (entlast) "" "4800,900" "4800,901" "No")
(setq tap15 (ssadd (entlast) tap15))
(setq coords (list 
(list 4800 868.55) 
(list 4800.135 868.55) 
(list 4800.135 868.5603) 
(list 4800.135 868.5706) 
(list 4800.135 868.5808) 
(list 4800.135 868.5911) 
(list 4800.135 868.6014) 
(list 4800.135 868.6117) 
(list 4800.135 868.6219) 
(list 4800.135 868.6322) 
(list 4800.135 868.6425) 
(list 4800.135 868.6528) 
(list 4800.135 868.6631) 
(list 4800.135 868.6733) 
(list 4800.135 868.6836) 
(list 4800.135 868.6939) 
(list 4800.135 868.7042) 
(list 4800.135 868.7144) 
(list 4800.135 868.7247) 
(list 4800.135 868.735) 
(list 4800.135 868.7453) 
(list 4800.135 868.7556) 
(list 4800.135 868.7658) 
(list 4800.135 868.7761) 
(list 4800.135 868.7864) 
(list 4800.135 868.7967) 
(list 4800.135 868.8069) 
(list 4800.135 868.8172) 
(list 4800.135 868.8275) 
(list 4800.135 868.8378) 
(list 4800.135 868.8481) 
(list 4800.135 868.8583) 
(list 4800.135 868.8686) 
(list 4800.135 868.8789) 
(list 4800.135 868.8892) 
(list 4800.135 868.8994) 
(list 4800.135 868.9097) 
(list 4800.135 868.92) 
(list 4800 868.92)))
(apply 'command (append '("pline") coords '("c")))
(setq tap15 (ssadd (entlast) tap15))
(command "_mirror" (entlast) "" "4800,900" "4800,901" "No")
(setq tap15 (ssadd (entlast) tap15))
(setq coords (list 
(list 4800.4722 868.55) 
(list 4800.4627 868.55) 
(list 4800.4623 868.5603) 
(list 4800.4605 868.5706) 
(list 4800.4575 868.5808) 
(list 4800.4532 868.5911) 
(list 4800.4478 868.6014) 
(list 4800.4415 868.6117) 
(list 4800.4344 868.6219) 
(list 4800.4268 868.6322) 
(list 4800.4189 868.6425) 
(list 4800.4108 868.6528) 
(list 4800.4029 868.6631) 
(list 4800.3954 868.6733) 
(list 4800.3886 868.6836) 
(list 4800.3826 868.6939) 
(list 4800.3777 868.7042) 
(list 4800.374 868.7144) 
(list 4800.3716 868.7247) 
(list 4800.3706 868.735) 
(list 4800.3711 868.7453) 
(list 4800.3731 868.7556) 
(list 4800.3765 868.7658) 
(list 4800.3813 868.7761) 
(list 4800.3872 868.7864) 
(list 4800.3942 868.7967) 
(list 4800.402 868.8069) 
(list 4800.4105 868.8172) 
(list 4800.4192 868.8275) 
(list 4800.4281 868.8378) 
(list 4800.4367 868.8481) 
(list 4800.4449 868.8583) 
(list 4800.4525 868.8686) 
(list 4800.459 868.8789) 
(list 4800.4644 868.8892) 
(list 4800.4685 868.8994) 
(list 4800.4711 868.9097) 
(list 4800.4722 868.92) 
(list 4800.4722 868.92)))
(apply 'command (append '("pline") coords '("c")))
(setq tap15 (ssadd (entlast) tap15))
(command "_mirror" (entlast) "" "4800,900" "4800,901" "No")
(setq tap15 (ssadd (entlast) tap15))
(setq coords (list 
(list 4801.116 868.55) 
(list 4800.4722 868.55) 
(list 4800.4722 868.5603) 
(list 4800.4722 868.5706) 
(list 4800.4722 868.5808) 
(list 4800.4722 868.5911) 
(list 4800.4722 868.6014) 
(list 4800.4722 868.6117) 
(list 4800.4722 868.6219) 
(list 4800.4722 868.6322) 
(list 4800.4722 868.6425) 
(list 4800.4722 868.6528) 
(list 4800.4722 868.6631) 
(list 4800.4722 868.6733) 
(list 4800.4722 868.6836) 
(list 4800.4722 868.6939) 
(list 4800.4722 868.7042) 
(list 4800.4722 868.7144) 
(list 4800.4722 868.7247) 
(list 4800.4722 868.735) 
(list 4800.4722 868.7453) 
(list 4800.4722 868.7556) 
(list 4800.4722 868.7658) 
(list 4800.4722 868.7761) 
(list 4800.4722 868.7864) 
(list 4800.4722 868.7967) 
(list 4800.4722 868.8069) 
(list 4800.4722 868.8172) 
(list 4800.4722 868.8275) 
(list 4800.4722 868.8378) 
(list 4800.4722 868.8481) 
(list 4800.4722 868.8583) 
(list 4800.4722 868.8686) 
(list 4800.4722 868.8789) 
(list 4800.4722 868.8892) 
(list 4800.4722 868.8994) 
(list 4800.4722 868.9097) 
(list 4800.4722 868.92) 
(list 4801.116 868.92)))
(apply 'command (append '("pline") coords '("c")))
(setq tap15 (ssadd (entlast) tap15))
(command "_mirror" (entlast) "" "4800,900" "4800,901" "No")
(setq tap15 (ssadd (entlast) tap15))
(setq coords (list 
(list 4800 868.92) 
(list 4800.135 868.92) 
(list 4800.135 868.9303) 
(list 4800.135 868.9406) 
(list 4800.135 868.9508) 
(list 4800.135 868.9611) 
(list 4800.135 868.9714) 
(list 4800.135 868.9817) 
(list 4800.135 868.9919) 
(list 4800.135 869.0022) 
(list 4800.135 869.0125) 
(list 4800.135 869.0228) 
(list 4800.135 869.0331) 
(list 4800.135 869.0433) 
(list 4800.135 869.0536) 
(list 4800.135 869.0639) 
(list 4800.135 869.0742) 
(list 4800.135 869.0844) 
(list 4800.135 869.0947) 
(list 4800.135 869.105) 
(list 4800.135 869.1153) 
(list 4800.135 869.1256) 
(list 4800.135 869.1358) 
(list 4800.135 869.1461) 
(list 4800.135 869.1564) 
(list 4800.135 869.1667) 
(list 4800.135 869.1769) 
(list 4800.135 869.1872) 
(list 4800.135 869.1975) 
(list 4800.135 869.2078) 
(list 4800.135 869.2181) 
(list 4800.135 869.2283) 
(list 4800.135 869.2386) 
(list 4800.135 869.2489) 
(list 4800.135 869.2592) 
(list 4800.135 869.2694) 
(list 4800.135 869.2797) 
(list 4800.135 869.29) 
(list 4800 869.29)))
(apply 'command (append '("pline") coords '("c")))
(setq tap15 (ssadd (entlast) tap15))
(command "_mirror" (entlast) "" "4800,900" "4800,901" "No")
(setq tap15 (ssadd (entlast) tap15))
(setq coords (list 
(list 4800.4817 868.92) 
(list 4800.4722 868.92) 
(list 4800.4717 868.9303) 
(list 4800.4695 868.9406) 
(list 4800.4658 868.9508) 
(list 4800.4607 868.9611) 
(list 4800.4542 868.9714) 
(list 4800.4467 868.9817) 
(list 4800.4382 868.9919) 
(list 4800.4291 869.0022) 
(list 4800.4196 869.0125) 
(list 4800.41 869.0228) 
(list 4800.4006 869.0331) 
(list 4800.3918 869.0433) 
(list 4800.3837 869.0536) 
(list 4800.3766 869.0639) 
(list 4800.3708 869.0742) 
(list 4800.3664 869.0844) 
(list 4800.3637 869.0947) 
(list 4800.3626 869.105) 
(list 4800.3632 869.1153) 
(list 4800.3656 869.1256) 
(list 4800.3697 869.1358) 
(list 4800.3753 869.1461) 
(list 4800.3823 869.1564) 
(list 4800.3906 869.1667) 
(list 4800.3998 869.1769) 
(list 4800.4097 869.1872) 
(list 4800.42 869.1975) 
(list 4800.4303 869.2078) 
(list 4800.4405 869.2181) 
(list 4800.4501 869.2283) 
(list 4800.4588 869.2386) 
(list 4800.4665 869.2489) 
(list 4800.4728 869.2592) 
(list 4800.4775 869.2694) 
(list 4800.4805 869.2797) 
(list 4800.4817 869.29) 
(list 4800.4817 869.29)))
(apply 'command (append '("pline") coords '("c")))
(setq tap15 (ssadd (entlast) tap15))
(command "_mirror" (entlast) "" "4800,900" "4800,901" "No")
(setq tap15 (ssadd (entlast) tap15))
(setq coords (list 
(list 4801.116 868.92) 
(list 4800.4817 868.92) 
(list 4800.4817 868.9303) 
(list 4800.4817 868.9406) 
(list 4800.4817 868.9508) 
(list 4800.4817 868.9611) 
(list 4800.4817 868.9714) 
(list 4800.4817 868.9817) 
(list 4800.4817 868.9919) 
(list 4800.4817 869.0022) 
(list 4800.4817 869.0125) 
(list 4800.4817 869.0228) 
(list 4800.4817 869.0331) 
(list 4800.4817 869.0433) 
(list 4800.4817 869.0536) 
(list 4800.4817 869.0639) 
(list 4800.4817 869.0742) 
(list 4800.4817 869.0844) 
(list 4800.4817 869.0947) 
(list 4800.4817 869.105) 
(list 4800.4817 869.1153) 
(list 4800.4817 869.1256) 
(list 4800.4817 869.1358) 
(list 4800.4817 869.1461) 
(list 4800.4817 869.1564) 
(list 4800.4817 869.1667) 
(list 4800.4817 869.1769) 
(list 4800.4817 869.1872) 
(list 4800.4817 869.1975) 
(list 4800.4817 869.2078) 
(list 4800.4817 869.2181) 
(list 4800.4817 869.2283) 
(list 4800.4817 869.2386) 
(list 4800.4817 869.2489) 
(list 4800.4817 869.2592) 
(list 4800.4817 869.2694) 
(list 4800.4817 869.2797) 
(list 4800.4817 869.29) 
(list 4801.116 869.29)))
(apply 'command (append '("pline") coords '("c")))
(setq tap15 (ssadd (entlast) tap15))
(command "_mirror" (entlast) "" "4800,900" "4800,901" "No")
(setq tap15 (ssadd (entlast) tap15))
(setq coords (list 
(list 4800 869.29) 
(list 4800.135 869.29) 
(list 4800.135 869.3003) 
(list 4800.135 869.3106) 
(list 4800.135 869.3208) 
(list 4800.135 869.3311) 
(list 4800.135 869.3414) 
(list 4800.135 869.3517) 
(list 4800.135 869.3619) 
(list 4800.135 869.3722) 
(list 4800.135 869.3825) 
(list 4800.135 869.3928) 
(list 4800.135 869.4031) 
(list 4800.135 869.4133) 
(list 4800.135 869.4236) 
(list 4800.135 869.4339) 
(list 4800.135 869.4442) 
(list 4800.135 869.4544) 
(list 4800.135 869.4647) 
(list 4800.135 869.475) 
(list 4800.135 869.4853) 
(list 4800.135 869.4956) 
(list 4800.135 869.5058) 
(list 4800.135 869.5161) 
(list 4800.135 869.5264) 
(list 4800.135 869.5367) 
(list 4800.135 869.5469) 
(list 4800.135 869.5572) 
(list 4800.135 869.5675) 
(list 4800.135 869.5778) 
(list 4800.135 869.5881) 
(list 4800.135 869.5983) 
(list 4800.135 869.6086) 
(list 4800.135 869.6189) 
(list 4800.135 869.6292) 
(list 4800.135 869.6394) 
(list 4800.135 869.6497) 
(list 4800.135 869.66) 
(list 4800 869.66)))
(apply 'command (append '("pline") coords '("c")))
(setq tap15 (ssadd (entlast) tap15))
(command "_mirror" (entlast) "" "4800,900" "4800,901" "No")
(setq tap15 (ssadd (entlast) tap15))
(setq coords (list 
(list 4800.4913 869.29) 
(list 4800.4817 869.29) 
(list 4800.4811 869.3003) 
(list 4800.4785 869.3106) 
(list 4800.4742 869.3208) 
(list 4800.4682 869.3311) 
(list 4800.4606 869.3414) 
(list 4800.4518 869.3517) 
(list 4800.4419 869.3619) 
(list 4800.4313 869.3722) 
(list 4800.4203 869.3825) 
(list 4800.4092 869.3928) 
(list 4800.3984 869.4031) 
(list 4800.3881 869.4133) 
(list 4800.3788 869.4236) 
(list 4800.3706 869.4339) 
(list 4800.3639 869.4442) 
(list 4800.3589 869.4544) 
(list 4800.3557 869.4647) 
(list 4800.3545 869.475) 
(list 4800.3553 869.4853) 
(list 4800.3581 869.4956) 
(list 4800.3628 869.5058) 
(list 4800.3693 869.5161) 
(list 4800.3774 869.5264) 
(list 4800.3869 869.5367) 
(list 4800.3975 869.5469) 
(list 4800.4089 869.5572) 
(list 4800.4207 869.5675) 
(list 4800.4326 869.5778) 
(list 4800.4442 869.5881) 
(list 4800.4552 869.5983) 
(list 4800.4652 869.6086) 
(list 4800.474 869.6189) 
(list 4800.4811 869.6292) 
(list 4800.4865 869.6394) 
(list 4800.4899 869.6497) 
(list 4800.4913 869.66) 
(list 4800.4913 869.66)))
(apply 'command (append '("pline") coords '("c")))
(setq tap15 (ssadd (entlast) tap15))
(command "_mirror" (entlast) "" "4800,900" "4800,901" "No")
(setq tap15 (ssadd (entlast) tap15))
(setq coords (list 
(list 4801.116 869.29) 
(list 4800.4913 869.29) 
(list 4800.4913 869.3003) 
(list 4800.4913 869.3106) 
(list 4800.4913 869.3208) 
(list 4800.4913 869.3311) 
(list 4800.4913 869.3414) 
(list 4800.4913 869.3517) 
(list 4800.4913 869.3619) 
(list 4800.4913 869.3722) 
(list 4800.4913 869.3825) 
(list 4800.4913 869.3928) 
(list 4800.4913 869.4031) 
(list 4800.4913 869.4133) 
(list 4800.4913 869.4236) 
(list 4800.4913 869.4339) 
(list 4800.4913 869.4442) 
(list 4800.4913 869.4544) 
(list 4800.4913 869.4647) 
(list 4800.4913 869.475) 
(list 4800.4913 869.4853) 
(list 4800.4913 869.4956) 
(list 4800.4913 869.5058) 
(list 4800.4913 869.5161) 
(list 4800.4913 869.5264) 
(list 4800.4913 869.5367) 
(list 4800.4913 869.5469) 
(list 4800.4913 869.5572) 
(list 4800.4913 869.5675) 
(list 4800.4913 869.5778) 
(list 4800.4913 869.5881) 
(list 4800.4913 869.5983) 
(list 4800.4913 869.6086) 
(list 4800.4913 869.6189) 
(list 4800.4913 869.6292) 
(list 4800.4913 869.6394) 
(list 4800.4913 869.6497) 
(list 4800.4913 869.66) 
(list 4801.116 869.66)))
(apply 'command (append '("pline") coords '("c")))
(setq tap15 (ssadd (entlast) tap15))
(command "_mirror" (entlast) "" "4800,900" "4800,901" "No")
(setq tap15 (ssadd (entlast) tap15))
(setq coords (list 
(list 4800 869.66) 
(list 4800.135 869.66) 
(list 4800.135 869.6703) 
(list 4800.135 869.6806) 
(list 4800.135 869.6908) 
(list 4800.135 869.7011) 
(list 4800.135 869.7114) 
(list 4800.135 869.7217) 
(list 4800.135 869.7319) 
(list 4800.135 869.7422) 
(list 4800.135 869.7525) 
(list 4800.135 869.7628) 
(list 4800.135 869.7731) 
(list 4800.135 869.7833) 
(list 4800.135 869.7936) 
(list 4800.135 869.8039) 
(list 4800.135 869.8142) 
(list 4800.135 869.8244) 
(list 4800.135 869.8347) 
(list 4800.135 869.845) 
(list 4800.135 869.8553) 
(list 4800.135 869.8656) 
(list 4800.135 869.8758) 
(list 4800.135 869.8861) 
(list 4800.135 869.8964) 
(list 4800.135 869.9067) 
(list 4800.135 869.9169) 
(list 4800.135 869.9272) 
(list 4800.135 869.9375) 
(list 4800.135 869.9478) 
(list 4800.135 869.9581) 
(list 4800.135 869.9683) 
(list 4800.135 869.9786) 
(list 4800.135 869.9889) 
(list 4800.135 869.9992) 
(list 4800.135 870.0094) 
(list 4800.135 870.0197) 
(list 4800.135 870.03) 
(list 4800 870.03)))
(apply 'command (append '("pline") coords '("c")))
(setq tap15 (ssadd (entlast) tap15))
(command "_mirror" (entlast) "" "4800,900" "4800,901" "No")
(setq tap15 (ssadd (entlast) tap15))
(setq coords (list 
(list 4800.5008 869.66) 
(list 4800.4913 869.66) 
(list 4800.4905 869.6703) 
(list 4800.4875 869.6806) 
(list 4800.4825 869.6908) 
(list 4800.4756 869.7011) 
(list 4800.467 869.7114) 
(list 4800.4569 869.7217) 
(list 4800.4457 869.7319) 
(list 4800.4336 869.7422) 
(list 4800.421 869.7525) 
(list 4800.4084 869.7628) 
(list 4800.3961 869.7731) 
(list 4800.3844 869.7833) 
(list 4800.3738 869.7936) 
(list 4800.3646 869.8039) 
(list 4800.357 869.8142) 
(list 4800.3514 869.8244) 
(list 4800.3478 869.8347) 
(list 4800.3464 869.845) 
(list 4800.3473 869.8553) 
(list 4800.3505 869.8656) 
(list 4800.3559 869.8758) 
(list 4800.3633 869.8861) 
(list 4800.3725 869.8964) 
(list 4800.3832 869.9067) 
(list 4800.3952 869.9169) 
(list 4800.4081 869.9272) 
(list 4800.4214 869.9375) 
(list 4800.4348 869.9478) 
(list 4800.448 869.9581) 
(list 4800.4603 869.9683) 
(list 4800.4716 869.9786) 
(list 4800.4814 869.9889) 
(list 4800.4895 869.9992) 
(list 4800.4955 870.0094) 
(list 4800.4993 870.0197) 
(list 4800.5008 870.03) 
(list 4800.5008 870.03)))
(apply 'command (append '("pline") coords '("c")))
(setq tap15 (ssadd (entlast) tap15))
(command "_mirror" (entlast) "" "4800,900" "4800,901" "No")
(setq tap15 (ssadd (entlast) tap15))
(setq coords (list 
(list 4801.116 869.66) 
(list 4800.5008 869.66) 
(list 4800.5008 869.6703) 
(list 4800.5008 869.6806) 
(list 4800.5008 869.6908) 
(list 4800.5008 869.7011) 
(list 4800.5008 869.7114) 
(list 4800.5008 869.7217) 
(list 4800.5008 869.7319) 
(list 4800.5008 869.7422) 
(list 4800.5008 869.7525) 
(list 4800.5008 869.7628) 
(list 4800.5008 869.7731) 
(list 4800.5008 869.7833) 
(list 4800.5008 869.7936) 
(list 4800.5008 869.8039) 
(list 4800.5008 869.8142) 
(list 4800.5008 869.8244) 
(list 4800.5008 869.8347) 
(list 4800.5008 869.845) 
(list 4800.5008 869.8553) 
(list 4800.5008 869.8656) 
(list 4800.5008 869.8758) 
(list 4800.5008 869.8861) 
(list 4800.5008 869.8964) 
(list 4800.5008 869.9067) 
(list 4800.5008 869.9169) 
(list 4800.5008 869.9272) 
(list 4800.5008 869.9375) 
(list 4800.5008 869.9478) 
(list 4800.5008 869.9581) 
(list 4800.5008 869.9683) 
(list 4800.5008 869.9786) 
(list 4800.5008 869.9889) 
(list 4800.5008 869.9992) 
(list 4800.5008 870.0094) 
(list 4800.5008 870.0197) 
(list 4800.5008 870.03) 
(list 4801.116 870.03)))
(apply 'command (append '("pline") coords '("c")))
(setq tap15 (ssadd (entlast) tap15))
(command "_mirror" (entlast) "" "4800,900" "4800,901" "No")
(setq tap15 (ssadd (entlast) tap15))
(setq coords (list 
(list 4800 870.03) 
(list 4800.135 870.03) 
(list 4800.135 870.0403) 
(list 4800.135 870.0506) 
(list 4800.135 870.0608) 
(list 4800.135 870.0711) 
(list 4800.135 870.0814) 
(list 4800.135 870.0917) 
(list 4800.135 870.1019) 
(list 4800.135 870.1122) 
(list 4800.135 870.1225) 
(list 4800.135 870.1328) 
(list 4800.135 870.1431) 
(list 4800.135 870.1533) 
(list 4800.135 870.1636) 
(list 4800.135 870.1739) 
(list 4800.135 870.1842) 
(list 4800.135 870.1944) 
(list 4800.135 870.2047) 
(list 4800.135 870.215) 
(list 4800.135 870.2253) 
(list 4800.135 870.2356) 
(list 4800.135 870.2458) 
(list 4800.135 870.2561) 
(list 4800.135 870.2664) 
(list 4800.135 870.2767) 
(list 4800.135 870.2869) 
(list 4800.135 870.2972) 
(list 4800.135 870.3075) 
(list 4800.135 870.3178) 
(list 4800.135 870.3281) 
(list 4800.135 870.3383) 
(list 4800.135 870.3486) 
(list 4800.135 870.3589) 
(list 4800.135 870.3692) 
(list 4800.135 870.3794) 
(list 4800.135 870.3897) 
(list 4800.135 870.4) 
(list 4800 870.4)))
(apply 'command (append '("pline") coords '("c")))
(setq tap15 (ssadd (entlast) tap15))
(command "_mirror" (entlast) "" "4800,900" "4800,901" "No")
(setq tap15 (ssadd (entlast) tap15))
(setq coords (list 
(list 4800.5103 870.03) 
(list 4800.5008 870.03) 
(list 4800.4999 870.0403) 
(list 4800.4965 870.0506) 
(list 4800.4909 870.0608) 
(list 4800.4831 870.0711) 
(list 4800.4734 870.0814) 
(list 4800.4621 870.0917) 
(list 4800.4494 870.1019) 
(list 4800.4359 870.1122) 
(list 4800.4218 870.1225) 
(list 4800.4076 870.1328) 
(list 4800.3938 870.1431) 
(list 4800.3808 870.1533) 
(list 4800.3689 870.1636) 
(list 4800.3586 870.1739) 
(list 4800.3501 870.1842) 
(list 4800.3438 870.1944) 
(list 4800.3399 870.2047) 
(list 4800.3384 870.215) 
(list 4800.3394 870.2253) 
(list 4800.343 870.2356) 
(list 4800.349 870.2458) 
(list 4800.3573 870.2561) 
(list 4800.3675 870.2664) 
(list 4800.3796 870.2767) 
(list 4800.3929 870.2869) 
(list 4800.4073 870.2972) 
(list 4800.4222 870.3075) 
(list 4800.4371 870.3178) 
(list 4800.4517 870.3281) 
(list 4800.4655 870.3383) 
(list 4800.478 870.3486) 
(list 4800.4889 870.3589) 
(list 4800.4978 870.3692) 
(list 4800.5045 870.3794) 
(list 4800.5087 870.3897) 
(list 4800.5103 870.4) 
(list 4800.5103 870.4)))
(apply 'command (append '("pline") coords '("c")))
(setq tap15 (ssadd (entlast) tap15))
(command "_mirror" (entlast) "" "4800,900" "4800,901" "No")
(setq tap15 (ssadd (entlast) tap15))
(setq coords (list 
(list 4801.116 870.03) 
(list 4800.5103 870.03) 
(list 4800.5103 870.0403) 
(list 4800.5103 870.0506) 
(list 4800.5103 870.0608) 
(list 4800.5103 870.0711) 
(list 4800.5103 870.0814) 
(list 4800.5103 870.0917) 
(list 4800.5103 870.1019) 
(list 4800.5103 870.1122) 
(list 4800.5103 870.1225) 
(list 4800.5103 870.1328) 
(list 4800.5103 870.1431) 
(list 4800.5103 870.1533) 
(list 4800.5103 870.1636) 
(list 4800.5103 870.1739) 
(list 4800.5103 870.1842) 
(list 4800.5103 870.1944) 
(list 4800.5103 870.2047) 
(list 4800.5103 870.215) 
(list 4800.5103 870.2253) 
(list 4800.5103 870.2356) 
(list 4800.5103 870.2458) 
(list 4800.5103 870.2561) 
(list 4800.5103 870.2664) 
(list 4800.5103 870.2767) 
(list 4800.5103 870.2869) 
(list 4800.5103 870.2972) 
(list 4800.5103 870.3075) 
(list 4800.5103 870.3178) 
(list 4800.5103 870.3281) 
(list 4800.5103 870.3383) 
(list 4800.5103 870.3486) 
(list 4800.5103 870.3589) 
(list 4800.5103 870.3692) 
(list 4800.5103 870.3794) 
(list 4800.5103 870.3897) 
(list 4800.5103 870.4) 
(list 4801.116 870.4)))
(apply 'command (append '("pline") coords '("c")))
(setq tap15 (ssadd (entlast) tap15))
(command "_mirror" (entlast) "" "4800,900" "4800,901" "No")
(setq tap15 (ssadd (entlast) tap15))
(setq coords (list 
(list 4800 870.4) 
(list 4800.135 870.4) 
(list 4800.135 870.4103) 
(list 4800.135 870.4206) 
(list 4800.135 870.4308) 
(list 4800.135 870.4411) 
(list 4800.135 870.4514) 
(list 4800.135 870.4617) 
(list 4800.135 870.4719) 
(list 4800.135 870.4822) 
(list 4800.135 870.4925) 
(list 4800.135 870.5028) 
(list 4800.135 870.5131) 
(list 4800.135 870.5233) 
(list 4800.135 870.5336) 
(list 4800.135 870.5439) 
(list 4800.135 870.5542) 
(list 4800.135 870.5644) 
(list 4800.135 870.5747) 
(list 4800.135 870.585) 
(list 4800.135 870.5953) 
(list 4800.135 870.6056) 
(list 4800.135 870.6158) 
(list 4800.135 870.6261) 
(list 4800.135 870.6364) 
(list 4800.135 870.6467) 
(list 4800.135 870.6569) 
(list 4800.135 870.6672) 
(list 4800.135 870.6775) 
(list 4800.135 870.6878) 
(list 4800.135 870.6981) 
(list 4800.135 870.7083) 
(list 4800.135 870.7186) 
(list 4800.135 870.7289) 
(list 4800.135 870.7392) 
(list 4800.135 870.7494) 
(list 4800.135 870.7597) 
(list 4800.135 870.77) 
(list 4800 870.77)))
(apply 'command (append '("pline") coords '("c")))
(setq tap15 (ssadd (entlast) tap15))
(command "_mirror" (entlast) "" "4800,900" "4800,901" "No")
(setq tap15 (ssadd (entlast) tap15))
(setq coords (list 
(list 4800.5199 870.4) 
(list 4800.5103 870.4) 
(list 4800.5093 870.4103) 
(list 4800.5055 870.4206) 
(list 4800.4992 870.4308) 
(list 4800.4906 870.4411) 
(list 4800.4798 870.4514) 
(list 4800.4672 870.4617) 
(list 4800.4532 870.4719) 
(list 4800.4381 870.4822) 
(list 4800.4225 870.4925) 
(list 4800.4068 870.5028) 
(list 4800.3915 870.5131) 
(list 4800.3771 870.5233) 
(list 4800.364 870.5336) 
(list 4800.3526 870.5439) 
(list 4800.3433 870.5542) 
(list 4800.3363 870.5644) 
(list 4800.3319 870.5747) 
(list 4800.3303 870.585) 
(list 4800.3315 870.5953) 
(list 4800.3355 870.6056) 
(list 4800.3421 870.6158) 
(list 4800.3512 870.6261) 
(list 4800.3626 870.6364) 
(list 4800.3759 870.6467) 
(list 4800.3907 870.6569) 
(list 4800.4065 870.6672) 
(list 4800.4229 870.6775) 
(list 4800.4394 870.6878) 
(list 4800.4554 870.6981) 
(list 4800.4706 870.7083) 
(list 4800.4844 870.7186) 
(list 4800.4964 870.7289) 
(list 4800.5062 870.7392) 
(list 4800.5135 870.7494) 
(list 4800.5181 870.7597) 
(list 4800.5199 870.77) 
(list 4800.5199 870.77)))
(apply 'command (append '("pline") coords '("c")))
(setq tap15 (ssadd (entlast) tap15))
(command "_mirror" (entlast) "" "4800,900" "4800,901" "No")
(setq tap15 (ssadd (entlast) tap15))
(setq coords (list 
(list 4801.116 870.4) 
(list 4800.5199 870.4) 
(list 4800.5199 870.4103) 
(list 4800.5199 870.4206) 
(list 4800.5199 870.4308) 
(list 4800.5199 870.4411) 
(list 4800.5199 870.4514) 
(list 4800.5199 870.4617) 
(list 4800.5199 870.4719) 
(list 4800.5199 870.4822) 
(list 4800.5199 870.4925) 
(list 4800.5199 870.5028) 
(list 4800.5199 870.5131) 
(list 4800.5199 870.5233) 
(list 4800.5199 870.5336) 
(list 4800.5199 870.5439) 
(list 4800.5199 870.5542) 
(list 4800.5199 870.5644) 
(list 4800.5199 870.5747) 
(list 4800.5199 870.585) 
(list 4800.5199 870.5953) 
(list 4800.5199 870.6056) 
(list 4800.5199 870.6158) 
(list 4800.5199 870.6261) 
(list 4800.5199 870.6364) 
(list 4800.5199 870.6467) 
(list 4800.5199 870.6569) 
(list 4800.5199 870.6672) 
(list 4800.5199 870.6775) 
(list 4800.5199 870.6878) 
(list 4800.5199 870.6981) 
(list 4800.5199 870.7083) 
(list 4800.5199 870.7186) 
(list 4800.5199 870.7289) 
(list 4800.5199 870.7392) 
(list 4800.5199 870.7494) 
(list 4800.5199 870.7597) 
(list 4800.5199 870.77) 
(list 4801.116 870.77)))
(apply 'command (append '("pline") coords '("c")))
(setq tap15 (ssadd (entlast) tap15))
(command "_mirror" (entlast) "" "4800,900" "4800,901" "No")
(setq tap15 (ssadd (entlast) tap15))
(setq coords (list 
(list 4800 870.77) 
(list 4800.135 870.77) 
(list 4800.135 870.7803) 
(list 4800.135 870.7906) 
(list 4800.135 870.8008) 
(list 4800.135 870.8111) 
(list 4800.135 870.8214) 
(list 4800.135 870.8317) 
(list 4800.135 870.8419) 
(list 4800.135 870.8522) 
(list 4800.135 870.8625) 
(list 4800.135 870.8728) 
(list 4800.135 870.8831) 
(list 4800.135 870.8933) 
(list 4800.135 870.9036) 
(list 4800.135 870.9139) 
(list 4800.135 870.9242) 
(list 4800.135 870.9344) 
(list 4800.135 870.9447) 
(list 4800.135 870.955) 
(list 4800.135 870.9653) 
(list 4800.135 870.9756) 
(list 4800.135 870.9858) 
(list 4800.135 870.9961) 
(list 4800.135 871.0064) 
(list 4800.135 871.0167) 
(list 4800.135 871.0269) 
(list 4800.135 871.0372) 
(list 4800.135 871.0475) 
(list 4800.135 871.0578) 
(list 4800.135 871.0681) 
(list 4800.135 871.0783) 
(list 4800.135 871.0886) 
(list 4800.135 871.0989) 
(list 4800.135 871.1092) 
(list 4800.135 871.1194) 
(list 4800.135 871.1297) 
(list 4800.135 871.14) 
(list 4800 871.14)))
(apply 'command (append '("pline") coords '("c")))
(setq tap15 (ssadd (entlast) tap15))
(command "_mirror" (entlast) "" "4800,900" "4800,901" "No")
(setq tap15 (ssadd (entlast) tap15))
(setq coords (list 
(list 4800.5294 870.77) 
(list 4800.5199 870.77) 
(list 4800.5187 870.7803) 
(list 4800.5145 870.7906) 
(list 4800.5076 870.8008) 
(list 4800.4981 870.8111) 
(list 4800.4862 870.8214) 
(list 4800.4723 870.8317) 
(list 4800.4569 870.8419) 
(list 4800.4404 870.8522) 
(list 4800.4232 870.8625) 
(list 4800.406 870.8728) 
(list 4800.3893 870.8831) 
(list 4800.3734 870.8933) 
(list 4800.3591 870.9036) 
(list 4800.3466 870.9139) 
(list 4800.3364 870.9242) 
(list 4800.3288 870.9344) 
(list 4800.324 870.9447) 
(list 4800.3222 870.955) 
(list 4800.3236 870.9653) 
(list 4800.3279 870.9756) 
(list 4800.3352 870.9858) 
(list 4800.3452 870.9961) 
(list 4800.3577 871.0064) 
(list 4800.3722 871.0167) 
(list 4800.3884 871.0269) 
(list 4800.4057 871.0372) 
(list 4800.4236 871.0475) 
(list 4800.4416 871.0578) 
(list 4800.4592 871.0681) 
(list 4800.4757 871.0783) 
(list 4800.4908 871.0886) 
(list 4800.5039 871.0989) 
(list 4800.5146 871.1092) 
(list 4800.5225 871.1194) 
(list 4800.5275 871.1297) 
(list 4800.5294 871.14) 
(list 4800.5294 871.14)))
(apply 'command (append '("pline") coords '("c")))
(setq tap15 (ssadd (entlast) tap15))
(command "_mirror" (entlast) "" "4800,900" "4800,901" "No")
(setq tap15 (ssadd (entlast) tap15))
(setq coords (list 
(list 4801.116 870.77) 
(list 4800.5294 870.77) 
(list 4800.5294 870.7803) 
(list 4800.5294 870.7906) 
(list 4800.5294 870.8008) 
(list 4800.5294 870.8111) 
(list 4800.5294 870.8214) 
(list 4800.5294 870.8317) 
(list 4800.5294 870.8419) 
(list 4800.5294 870.8522) 
(list 4800.5294 870.8625) 
(list 4800.5294 870.8728) 
(list 4800.5294 870.8831) 
(list 4800.5294 870.8933) 
(list 4800.5294 870.9036) 
(list 4800.5294 870.9139) 
(list 4800.5294 870.9242) 
(list 4800.5294 870.9344) 
(list 4800.5294 870.9447) 
(list 4800.5294 870.955) 
(list 4800.5294 870.9653) 
(list 4800.5294 870.9756) 
(list 4800.5294 870.9858) 
(list 4800.5294 870.9961) 
(list 4800.5294 871.0064) 
(list 4800.5294 871.0167) 
(list 4800.5294 871.0269) 
(list 4800.5294 871.0372) 
(list 4800.5294 871.0475) 
(list 4800.5294 871.0578) 
(list 4800.5294 871.0681) 
(list 4800.5294 871.0783) 
(list 4800.5294 871.0886) 
(list 4800.5294 871.0989) 
(list 4800.5294 871.1092) 
(list 4800.5294 871.1194) 
(list 4800.5294 871.1297) 
(list 4800.5294 871.14) 
(list 4801.116 871.14)))
(apply 'command (append '("pline") coords '("c")))
(setq tap15 (ssadd (entlast) tap15))
(command "_mirror" (entlast) "" "4800,900" "4800,901" "No")
(setq tap15 (ssadd (entlast) tap15))
(setq coords (list 
(list 4800 871.14) 
(list 4800.135 871.14) 
(list 4800.135 871.1503) 
(list 4800.135 871.1606) 
(list 4800.135 871.1708) 
(list 4800.135 871.1811) 
(list 4800.135 871.1914) 
(list 4800.135 871.2017) 
(list 4800.135 871.2119) 
(list 4800.135 871.2222) 
(list 4800.135 871.2325) 
(list 4800.135 871.2428) 
(list 4800.135 871.2531) 
(list 4800.135 871.2633) 
(list 4800.135 871.2736) 
(list 4800.135 871.2839) 
(list 4800.135 871.2942) 
(list 4800.135 871.3044) 
(list 4800.135 871.3147) 
(list 4800.135 871.325) 
(list 4800.135 871.3353) 
(list 4800.135 871.3456) 
(list 4800.135 871.3558) 
(list 4800.135 871.3661) 
(list 4800.135 871.3764) 
(list 4800.135 871.3867) 
(list 4800.135 871.3969) 
(list 4800.135 871.4072) 
(list 4800.135 871.4175) 
(list 4800.135 871.4278) 
(list 4800.135 871.4381) 
(list 4800.135 871.4483) 
(list 4800.135 871.4586) 
(list 4800.135 871.4689) 
(list 4800.135 871.4792) 
(list 4800.135 871.4894) 
(list 4800.135 871.4997) 
(list 4800.135 871.51) 
(list 4800 871.51)))
(apply 'command (append '("pline") coords '("c")))
(setq tap15 (ssadd (entlast) tap15))
(command "_mirror" (entlast) "" "4800,900" "4800,901" "No")
(setq tap15 (ssadd (entlast) tap15))
(setq coords (list 
(list 4800.5389 871.14) 
(list 4800.5294 871.14) 
(list 4800.5281 871.1503) 
(list 4800.5235 871.1606) 
(list 4800.5159 871.1708) 
(list 4800.5055 871.1811) 
(list 4800.4926 871.1914) 
(list 4800.4775 871.2017) 
(list 4800.4606 871.2119) 
(list 4800.4426 871.2222) 
(list 4800.424 871.2325) 
(list 4800.4052 871.2428) 
(list 4800.387 871.2531) 
(list 4800.3698 871.2633) 
(list 4800.3541 871.2736) 
(list 4800.3406 871.2839) 
(list 4800.3295 871.2942) 
(list 4800.3212 871.3044) 
(list 4800.3161 871.3147) 
(list 4800.3142 871.325) 
(list 4800.3156 871.3353) 
(list 4800.3204 871.3456) 
(list 4800.3283 871.3558) 
(list 4800.3392 871.3661) 
(list 4800.3528 871.3764) 
(list 4800.3686 871.3867) 
(list 4800.3861 871.3969) 
(list 4800.4049 871.4072) 
(list 4800.4244 871.4175) 
(list 4800.4439 871.4278) 
(list 4800.4629 871.4381) 
(list 4800.4809 871.4483) 
(list 4800.4972 871.4586) 
(list 4800.5113 871.4689) 
(list 4800.5229 871.4792) 
(list 4800.5315 871.4894) 
(list 4800.5369 871.4997) 
(list 4800.5389 871.51) 
(list 4800.5389 871.51)))
(apply 'command (append '("pline") coords '("c")))
(setq tap15 (ssadd (entlast) tap15))
(command "_mirror" (entlast) "" "4800,900" "4800,901" "No")
(setq tap15 (ssadd (entlast) tap15))
(setq coords (list 
(list 4801.116 871.14) 
(list 4800.5389 871.14) 
(list 4800.5389 871.1503) 
(list 4800.5389 871.1606) 
(list 4800.5389 871.1708) 
(list 4800.5389 871.1811) 
(list 4800.5389 871.1914) 
(list 4800.5389 871.2017) 
(list 4800.5389 871.2119) 
(list 4800.5389 871.2222) 
(list 4800.5389 871.2325) 
(list 4800.5389 871.2428) 
(list 4800.5389 871.2531) 
(list 4800.5389 871.2633) 
(list 4800.5389 871.2736) 
(list 4800.5389 871.2839) 
(list 4800.5389 871.2942) 
(list 4800.5389 871.3044) 
(list 4800.5389 871.3147) 
(list 4800.5389 871.325) 
(list 4800.5389 871.3353) 
(list 4800.5389 871.3456) 
(list 4800.5389 871.3558) 
(list 4800.5389 871.3661) 
(list 4800.5389 871.3764) 
(list 4800.5389 871.3867) 
(list 4800.5389 871.3969) 
(list 4800.5389 871.4072) 
(list 4800.5389 871.4175) 
(list 4800.5389 871.4278) 
(list 4800.5389 871.4381) 
(list 4800.5389 871.4483) 
(list 4800.5389 871.4586) 
(list 4800.5389 871.4689) 
(list 4800.5389 871.4792) 
(list 4800.5389 871.4894) 
(list 4800.5389 871.4997) 
(list 4800.5389 871.51) 
(list 4801.116 871.51)))
(apply 'command (append '("pline") coords '("c")))
(setq tap15 (ssadd (entlast) tap15))
(command "_mirror" (entlast) "" "4800,900" "4800,901" "No")
(setq tap15 (ssadd (entlast) tap15))
(setq coords (list 
(list 4800 871.51) 
(list 4800.135 871.51) 
(list 4800.135 871.5203) 
(list 4800.135 871.5306) 
(list 4800.135 871.5408) 
(list 4800.135 871.5511) 
(list 4800.135 871.5614) 
(list 4800.135 871.5717) 
(list 4800.135 871.5819) 
(list 4800.135 871.5922) 
(list 4800.135 871.6025) 
(list 4800.135 871.6128) 
(list 4800.135 871.6231) 
(list 4800.135 871.6333) 
(list 4800.135 871.6436) 
(list 4800.135 871.6539) 
(list 4800.135 871.6642) 
(list 4800.135 871.6744) 
(list 4800.135 871.6847) 
(list 4800.135 871.695) 
(list 4800.135 871.7053) 
(list 4800.135 871.7156) 
(list 4800.135 871.7258) 
(list 4800.135 871.7361) 
(list 4800.135 871.7464) 
(list 4800.135 871.7567) 
(list 4800.135 871.7669) 
(list 4800.135 871.7772) 
(list 4800.135 871.7875) 
(list 4800.135 871.7978) 
(list 4800.135 871.8081) 
(list 4800.135 871.8183) 
(list 4800.135 871.8286) 
(list 4800.135 871.8389) 
(list 4800.135 871.8492) 
(list 4800.135 871.8594) 
(list 4800.135 871.8697) 
(list 4800.135 871.88) 
(list 4800 871.88)))
(apply 'command (append '("pline") coords '("c")))
(setq tap15 (ssadd (entlast) tap15))
(command "_mirror" (entlast) "" "4800,900" "4800,901" "No")
(setq tap15 (ssadd (entlast) tap15))
(setq coords (list 
(list 4800.5485 871.51) 
(list 4800.5389 871.51) 
(list 4800.5375 871.5203) 
(list 4800.5325 871.5306) 
(list 4800.5243 871.5408) 
(list 4800.513 871.5511) 
(list 4800.499 871.5614) 
(list 4800.4826 871.5717) 
(list 4800.4644 871.5819) 
(list 4800.4449 871.5922) 
(list 4800.4247 871.6025) 
(list 4800.4044 871.6128) 
(list 4800.3847 871.6231) 
(list 4800.3661 871.6333) 
(list 4800.3492 871.6436) 
(list 4800.3346 871.6539) 
(list 4800.3226 871.6642) 
(list 4800.3137 871.6744) 
(list 4800.3081 871.6847) 
(list 4800.3061 871.695) 
(list 4800.3077 871.7053) 
(list 4800.3128 871.7156) 
(list 4800.3214 871.7258) 
(list 4800.3332 871.7361) 
(list 4800.3479 871.7464) 
(list 4800.3649 871.7567) 
(list 4800.3838 871.7669) 
(list 4800.4041 871.7772) 
(list 4800.4251 871.7875) 
(list 4800.4462 871.7978) 
(list 4800.4667 871.8081) 
(list 4800.486 871.8183) 
(list 4800.5036 871.8286) 
(list 4800.5188 871.8389) 
(list 4800.5313 871.8492) 
(list 4800.5405 871.8594) 
(list 4800.5463 871.8697) 
(list 4800.5485 871.88) 
(list 4800.5485 871.88)))
(apply 'command (append '("pline") coords '("c")))
(setq tap15 (ssadd (entlast) tap15))
(command "_mirror" (entlast) "" "4800,900" "4800,901" "No")
(setq tap15 (ssadd (entlast) tap15))
(setq coords (list 
(list 4801.116 871.51) 
(list 4800.5485 871.51) 
(list 4800.5485 871.5203) 
(list 4800.5485 871.5306) 
(list 4800.5485 871.5408) 
(list 4800.5485 871.5511) 
(list 4800.5485 871.5614) 
(list 4800.5485 871.5717) 
(list 4800.5485 871.5819) 
(list 4800.5485 871.5922) 
(list 4800.5485 871.6025) 
(list 4800.5485 871.6128) 
(list 4800.5485 871.6231) 
(list 4800.5485 871.6333) 
(list 4800.5485 871.6436) 
(list 4800.5485 871.6539) 
(list 4800.5485 871.6642) 
(list 4800.5485 871.6744) 
(list 4800.5485 871.6847) 
(list 4800.5485 871.695) 
(list 4800.5485 871.7053) 
(list 4800.5485 871.7156) 
(list 4800.5485 871.7258) 
(list 4800.5485 871.7361) 
(list 4800.5485 871.7464) 
(list 4800.5485 871.7567) 
(list 4800.5485 871.7669) 
(list 4800.5485 871.7772) 
(list 4800.5485 871.7875) 
(list 4800.5485 871.7978) 
(list 4800.5485 871.8081) 
(list 4800.5485 871.8183) 
(list 4800.5485 871.8286) 
(list 4800.5485 871.8389) 
(list 4800.5485 871.8492) 
(list 4800.5485 871.8594) 
(list 4800.5485 871.8697) 
(list 4800.5485 871.88) 
(list 4801.116 871.88)))
(apply 'command (append '("pline") coords '("c")))
(setq tap15 (ssadd (entlast) tap15))
(command "_mirror" (entlast) "" "4800,900" "4800,901" "No")
(setq tap15 (ssadd (entlast) tap15))
(setq coords (list 
(list 4800 871.88) 
(list 4800.135 871.88) 
(list 4800.135 871.8903) 
(list 4800.135 871.9006) 
(list 4800.135 871.9108) 
(list 4800.135 871.9211) 
(list 4800.135 871.9314) 
(list 4800.135 871.9417) 
(list 4800.135 871.9519) 
(list 4800.135 871.9622) 
(list 4800.135 871.9725) 
(list 4800.135 871.9828) 
(list 4800.135 871.9931) 
(list 4800.135 872.0033) 
(list 4800.135 872.0136) 
(list 4800.135 872.0239) 
(list 4800.135 872.0342) 
(list 4800.135 872.0444) 
(list 4800.135 872.0547) 
(list 4800.135 872.065) 
(list 4800.135 872.0753) 
(list 4800.135 872.0856) 
(list 4800.135 872.0958) 
(list 4800.135 872.1061) 
(list 4800.135 872.1164) 
(list 4800.135 872.1267) 
(list 4800.135 872.1369) 
(list 4800.135 872.1472) 
(list 4800.135 872.1575) 
(list 4800.135 872.1678) 
(list 4800.135 872.1781) 
(list 4800.135 872.1883) 
(list 4800.135 872.1986) 
(list 4800.135 872.2089) 
(list 4800.135 872.2192) 
(list 4800.135 872.2294) 
(list 4800.135 872.2397) 
(list 4800.135 872.25) 
(list 4800 872.25)))
(apply 'command (append '("pline") coords '("c")))
(setq tap15 (ssadd (entlast) tap15))
(command "_mirror" (entlast) "" "4800,900" "4800,901" "No")
(setq tap15 (ssadd (entlast) tap15))
(setq coords (list 
(list 4800.558 871.88) 
(list 4800.5485 871.88) 
(list 4800.5469 871.8903) 
(list 4800.5415 871.9006) 
(list 4800.5327 871.9108) 
(list 4800.5205 871.9211) 
(list 4800.5053 871.9314) 
(list 4800.4877 871.9417) 
(list 4800.4681 871.9519) 
(list 4800.4472 871.9622) 
(list 4800.4254 871.9725) 
(list 4800.4037 871.9828) 
(list 4800.3824 871.9931) 
(list 4800.3624 872.0033) 
(list 4800.3443 872.0136) 
(list 4800.3286 872.0239) 
(list 4800.3157 872.0342) 
(list 4800.3061 872.0444) 
(list 4800.3002 872.0547) 
(list 4800.298 872.065) 
(list 4800.2998 872.0753) 
(list 4800.3053 872.0856) 
(list 4800.3146 872.0958) 
(list 4800.3272 872.1061) 
(list 4800.3429 872.1164) 
(list 4800.3612 872.1267) 
(list 4800.3815 872.1369) 
(list 4800.4033 872.1472) 
(list 4800.4258 872.1575) 
(list 4800.4484 872.1678) 
(list 4800.4704 872.1781) 
(list 4800.4911 872.1883) 
(list 4800.51 872.1986) 
(list 4800.5263 872.2089) 
(list 4800.5396 872.2192) 
(list 4800.5495 872.2294) 
(list 4800.5557 872.2397) 
(list 4800.558 872.25) 
(list 4800.558 872.25)))
(apply 'command (append '("pline") coords '("c")))
(setq tap15 (ssadd (entlast) tap15))
(command "_mirror" (entlast) "" "4800,900" "4800,901" "No")
(setq tap15 (ssadd (entlast) tap15))
(setq coords (list 
(list 4801.116 871.88) 
(list 4800.558 871.88) 
(list 4800.558 871.8903) 
(list 4800.558 871.9006) 
(list 4800.558 871.9108) 
(list 4800.558 871.9211) 
(list 4800.558 871.9314) 
(list 4800.558 871.9417) 
(list 4800.558 871.9519) 
(list 4800.558 871.9622) 
(list 4800.558 871.9725) 
(list 4800.558 871.9828) 
(list 4800.558 871.9931) 
(list 4800.558 872.0033) 
(list 4800.558 872.0136) 
(list 4800.558 872.0239) 
(list 4800.558 872.0342) 
(list 4800.558 872.0444) 
(list 4800.558 872.0547) 
(list 4800.558 872.065) 
(list 4800.558 872.0753) 
(list 4800.558 872.0856) 
(list 4800.558 872.0958) 
(list 4800.558 872.1061) 
(list 4800.558 872.1164) 
(list 4800.558 872.1267) 
(list 4800.558 872.1369) 
(list 4800.558 872.1472) 
(list 4800.558 872.1575) 
(list 4800.558 872.1678) 
(list 4800.558 872.1781) 
(list 4800.558 872.1883) 
(list 4800.558 872.1986) 
(list 4800.558 872.2089) 
(list 4800.558 872.2192) 
(list 4800.558 872.2294) 
(list 4800.558 872.2397) 
(list 4800.558 872.25) 
(list 4801.116 872.25)))
(apply 'command (append '("pline") coords '("c")))
(setq tap15 (ssadd (entlast) tap15))
(command "_mirror" (entlast) "" "4800,900" "4800,901" "No")
(setq tap15 (ssadd (entlast) tap15))
(command "_block" "blktap15" "4800,900" tap15 "")
(command "_insert" "blktap15" "4800,900" "1" "1" "0")
(command "_insert" "blktap15" "4800,900" "1" "1" "180")
(setq uc15 nil)
(setq uc15 (ssadd))
(setq coords (list 
(list 0 -0.185) 
(list 0.135 -0.185) 
(list 0.135 -0.17472) 
(list 0.135 -0.16444) 
(list 0.135 -0.15417) 
(list 0.135 -0.14389) 
(list 0.135 -0.13361) 
(list 0.135 -0.12333) 
(list 0.135 -0.11306) 
(list 0.135 -0.10278) 
(list 0.135 -0.0925) 
(list 0.135 -0.082222) 
(list 0.135 -0.071944) 
(list 0.135 -0.061667) 
(list 0.135 -0.051389) 
(list 0.135 -0.041111) 
(list 0.135 -0.030833) 
(list 0.135 -0.020556) 
(list 0.135 -0.010278) 
(list 0.135 0) 
(list 0.135 0.010278) 
(list 0.135 0.020556) 
(list 0.135 0.030833) 
(list 0.135 0.041111) 
(list 0.135 0.051389) 
(list 0.135 0.061667) 
(list 0.135 0.071944) 
(list 0.135 0.082222) 
(list 0.135 0.0925) 
(list 0.135 0.10278) 
(list 0.135 0.11306) 
(list 0.135 0.12333) 
(list 0.135 0.13361) 
(list 0.135 0.14389) 
(list 0.135 0.15417) 
(list 0.135 0.16444) 
(list 0.135 0.17472) 
(list 0.135 0.185) 
(list 0 0.185)))
(apply 'command (append '("pline") coords '("c")))
(setq uc15 (ssadd (entlast) uc15))
(setq coords (list 
(list 1.116 -0.185) 
(list 0.558 -0.185) 
(list 0.556 -0.17472) 
(list 0.55004 -0.16444) 
(list 0.54031 -0.15417) 
(list 0.52712 -0.14389) 
(list 0.51085 -0.13361) 
(list 0.492 -0.12333) 
(list 0.47115 -0.11306) 
(list 0.44892 -0.10278) 
(list 0.426 -0.0925) 
(list 0.40308 -0.082222) 
(list 0.38085 -0.071944) 
(list 0.36 -0.061667) 
(list 0.34115 -0.051389) 
(list 0.32488 -0.041111) 
(list 0.31168 -0.030833) 
(list 0.30196 -0.020556) 
(list 0.29601 -0.010278) 
(list 0.294 0) 
(list 0.29601 0.010278) 
(list 0.30196 0.020556) 
(list 0.31168 0.030833) 
(list 0.32488 0.041111) 
(list 0.34115 0.051389) 
(list 0.36 0.061667) 
(list 0.38085 0.071944) 
(list 0.40308 0.082222) 
(list 0.426 0.0925) 
(list 0.44892 0.10278) 
(list 0.47115 0.11306) 
(list 0.492 0.12333) 
(list 0.51085 0.13361) 
(list 0.52712 0.14389) 
(list 0.54031 0.15417) 
(list 0.55004 0.16444) 
(list 0.556 0.17472) 
(list 0.558 0.185) 
(list 1.116 0.185)))
(apply 'command (append '("pline") coords '("c")))
(setq uc15 (ssadd (entlast) uc15))
(command "_block" "blkuc15" "0,0.185" uc15 "")
(command "_insert" "blkuc15" "4800,872.62" "1" "1" "0")
(command "_insert" "blkuc15" "4800,872.25" "1" "1" "180")
(command "_insert" "blkuc15" "4800,872.99" "1" "1" "0")
(command "_insert" "blkuc15" "4800,872.62" "1" "1" "180")
(command "_insert" "blkuc15" "4800,873.36" "1" "1" "0")
(command "_insert" "blkuc15" "4800,872.99" "1" "1" "180")
(command "_insert" "blkuc15" "4800,873.73" "1" "1" "0")
(command "_insert" "blkuc15" "4800,873.36" "1" "1" "180")
(command "_insert" "blkuc15" "4800,874.1" "1" "1" "0")
(command "_insert" "blkuc15" "4800,873.73" "1" "1" "180")
(command "_insert" "blkuc15" "4800,874.47" "1" "1" "0")
(command "_insert" "blkuc15" "4800,874.1" "1" "1" "180")
(command "_insert" "blkuc15" "4800,874.84" "1" "1" "0")
(command "_insert" "blkuc15" "4800,874.47" "1" "1" "180")
(command "_insert" "blkuc15" "4800,875.21" "1" "1" "0")
(command "_insert" "blkuc15" "4800,874.84" "1" "1" "180")
(command "_insert" "blkuc15" "4800,875.58" "1" "1" "0")
(command "_insert" "blkuc15" "4800,875.21" "1" "1" "180")
(command "_insert" "blkuc15" "4800,875.95" "1" "1" "0")
(command "_insert" "blkuc15" "4800,875.58" "1" "1" "180")
(command "_insert" "blkuc15" "4800,876.32" "1" "1" "0")
(command "_insert" "blkuc15" "4800,875.95" "1" "1" "180")
(command "_insert" "blkuc15" "4800,876.69" "1" "1" "0")
(command "_insert" "blkuc15" "4800,876.32" "1" "1" "180")
(command "_insert" "blkuc15" "4800,877.06" "1" "1" "0")
(command "_insert" "blkuc15" "4800,876.69" "1" "1" "180")
(command "_insert" "blkuc15" "4800,877.43" "1" "1" "0")
(command "_insert" "blkuc15" "4800,877.06" "1" "1" "180")
(command "_insert" "blkuc15" "4800,877.8" "1" "1" "0")
(command "_insert" "blkuc15" "4800,877.43" "1" "1" "180")
(command "_insert" "blkuc15" "4800,878.17" "1" "1" "0")
(command "_insert" "blkuc15" "4800,877.8" "1" "1" "180")
(command "_insert" "blkuc15" "4800,878.54" "1" "1" "0")
(command "_insert" "blkuc15" "4800,878.17" "1" "1" "180")
(command "_insert" "blkuc15" "4800,878.91" "1" "1" "0")
(command "_insert" "blkuc15" "4800,878.54" "1" "1" "180")
(command "_insert" "blkuc15" "4800,879.28" "1" "1" "0")
(command "_insert" "blkuc15" "4800,878.91" "1" "1" "180")
(command "_insert" "blkuc15" "4800,879.65" "1" "1" "0")
(command "_insert" "blkuc15" "4800,879.28" "1" "1" "180")
(command "_insert" "blkuc15" "4800,880.02" "1" "1" "0")
(command "_insert" "blkuc15" "4800,879.65" "1" "1" "180")
(command "_insert" "blkuc15" "4800,880.39" "1" "1" "0")
(command "_insert" "blkuc15" "4800,880.02" "1" "1" "180")
(command "_insert" "blkuc15" "4800,880.76" "1" "1" "0")
(command "_insert" "blkuc15" "4800,880.39" "1" "1" "180")
(command "_insert" "blkuc15" "4800,881.13" "1" "1" "0")
(command "_insert" "blkuc15" "4800,880.76" "1" "1" "180")
(command "_insert" "blkuc15" "4800,881.5" "1" "1" "0")
(command "_insert" "blkuc15" "4800,881.13" "1" "1" "180")
(command "_insert" "blkuc15" "4800,881.87" "1" "1" "0")
(command "_insert" "blkuc15" "4800,881.5" "1" "1" "180")
(command "_insert" "blkuc15" "4800,882.24" "1" "1" "0")
(command "_insert" "blkuc15" "4800,881.87" "1" "1" "180")
(command "_insert" "blkuc15" "4800,882.61" "1" "1" "0")
(command "_insert" "blkuc15" "4800,882.24" "1" "1" "180")
(command "_insert" "blkuc15" "4800,882.98" "1" "1" "0")
(command "_insert" "blkuc15" "4800,882.61" "1" "1" "180")
(command "_insert" "blkuc15" "4800,883.35" "1" "1" "0")
(command "_insert" "blkuc15" "4800,882.98" "1" "1" "180")
(command "_insert" "blkuc15" "4800,883.72" "1" "1" "0")
(command "_insert" "blkuc15" "4800,883.35" "1" "1" "180")
(command "_insert" "blkuc15" "4800,884.09" "1" "1" "0")
(command "_insert" "blkuc15" "4800,883.72" "1" "1" "180")
(command "_insert" "blkuc15" "4800,884.46" "1" "1" "0")
(command "_insert" "blkuc15" "4800,884.09" "1" "1" "180")
(command "_insert" "blkuc15" "4800,884.83" "1" "1" "0")
(command "_insert" "blkuc15" "4800,884.46" "1" "1" "180")
(command "_insert" "blkuc15" "4800,885.2" "1" "1" "0")
(command "_insert" "blkuc15" "4800,884.83" "1" "1" "180")
(command "_insert" "blkuc15" "4800,885.57" "1" "1" "0")
(command "_insert" "blkuc15" "4800,885.2" "1" "1" "180")
(command "_insert" "blkuc15" "4800,885.94" "1" "1" "0")
(command "_insert" "blkuc15" "4800,885.57" "1" "1" "180")
(command "_insert" "blkuc15" "4800,886.31" "1" "1" "0")
(command "_insert" "blkuc15" "4800,885.94" "1" "1" "180")
(command "_insert" "blkuc15" "4800,886.68" "1" "1" "0")
(command "_insert" "blkuc15" "4800,886.31" "1" "1" "180")
(command "_insert" "blkuc15" "4800,887.05" "1" "1" "0")
(command "_insert" "blkuc15" "4800,886.68" "1" "1" "180")
(command "_insert" "blkuc15" "4800,887.42" "1" "1" "0")
(command "_insert" "blkuc15" "4800,887.05" "1" "1" "180")
(command "_insert" "blkuc15" "4800,887.79" "1" "1" "0")
(command "_insert" "blkuc15" "4800,887.42" "1" "1" "180")
(command "_insert" "blkuc15" "4800,888.16" "1" "1" "0")
(command "_insert" "blkuc15" "4800,887.79" "1" "1" "180")
(command "_insert" "blkuc15" "4800,888.53" "1" "1" "0")
(command "_insert" "blkuc15" "4800,888.16" "1" "1" "180")
(command "_insert" "blkuc15" "4800,888.9" "1" "1" "0")
(command "_insert" "blkuc15" "4800,888.53" "1" "1" "180")
(command "_insert" "blkuc15" "4800,889.27" "1" "1" "0")
(command "_insert" "blkuc15" "4800,888.9" "1" "1" "180")
(command "_insert" "blkuc15" "4800,889.64" "1" "1" "0")
(command "_insert" "blkuc15" "4800,889.27" "1" "1" "180")
(command "_insert" "blkuc15" "4800,890.01" "1" "1" "0")
(command "_insert" "blkuc15" "4800,889.64" "1" "1" "180")
(command "_insert" "blkuc15" "4800,890.38" "1" "1" "0")
(command "_insert" "blkuc15" "4800,890.01" "1" "1" "180")
(command "_insert" "blkuc15" "4800,890.75" "1" "1" "0")
(command "_insert" "blkuc15" "4800,890.38" "1" "1" "180")
(command "_insert" "blkuc15" "4800,891.12" "1" "1" "0")
(command "_insert" "blkuc15" "4800,890.75" "1" "1" "180")
(command "_insert" "blkuc15" "4800,891.49" "1" "1" "0")
(command "_insert" "blkuc15" "4800,891.12" "1" "1" "180")
(command "_insert" "blkuc15" "4800,891.86" "1" "1" "0")
(command "_insert" "blkuc15" "4800,891.49" "1" "1" "180")
(command "_insert" "blkuc15" "4800,892.23" "1" "1" "0")
(command "_insert" "blkuc15" "4800,891.86" "1" "1" "180")
(command "_insert" "blkuc15" "4800,892.6" "1" "1" "0")
(command "_insert" "blkuc15" "4800,892.23" "1" "1" "180")
(command "_insert" "blkuc15" "4800,892.97" "1" "1" "0")
(command "_insert" "blkuc15" "4800,892.6" "1" "1" "180")
(command "_insert" "blkuc15" "4800,893.34" "1" "1" "0")
(command "_insert" "blkuc15" "4800,892.97" "1" "1" "180")
(command "_insert" "blkuc15" "4800,893.71" "1" "1" "0")
(command "_insert" "blkuc15" "4800,893.34" "1" "1" "180")
(command "_insert" "blkuc15" "4800,894.08" "1" "1" "0")
(command "_insert" "blkuc15" "4800,893.71" "1" "1" "180")
(command "_insert" "blkuc15" "4800,894.45" "1" "1" "0")
(command "_insert" "blkuc15" "4800,894.08" "1" "1" "180")
(command "_insert" "blkuc15" "4800,894.82" "1" "1" "0")
(command "_insert" "blkuc15" "4800,894.45" "1" "1" "180")
(command "_insert" "blkuc15" "4800,895.19" "1" "1" "0")
(command "_insert" "blkuc15" "4800,894.82" "1" "1" "180")
(command "_insert" "blkuc15" "4800,895.56" "1" "1" "0")
(command "_insert" "blkuc15" "4800,895.19" "1" "1" "180")
(command "_insert" "blkuc15" "4800,895.93" "1" "1" "0")
(command "_insert" "blkuc15" "4800,895.56" "1" "1" "180")
(command "_insert" "blkuc15" "4800,896.3" "1" "1" "0")
(command "_insert" "blkuc15" "4800,895.93" "1" "1" "180")
(command "_insert" "blkuc15" "4800,896.67" "1" "1" "0")
(command "_insert" "blkuc15" "4800,896.3" "1" "1" "180")
(command "_insert" "blkuc15" "4800,897.04" "1" "1" "0")
(command "_insert" "blkuc15" "4800,896.67" "1" "1" "180")
(command "_insert" "blkuc15" "4800,897.41" "1" "1" "0")
(command "_insert" "blkuc15" "4800,897.04" "1" "1" "180")
(command "_insert" "blkuc15" "4800,897.78" "1" "1" "0")
(command "_insert" "blkuc15" "4800,897.41" "1" "1" "180")
(command "_insert" "blkuc15" "4800,898.15" "1" "1" "0")
(command "_insert" "blkuc15" "4800,897.78" "1" "1" "180")
(command "_insert" "blkuc15" "4800,898.52" "1" "1" "0")
(command "_insert" "blkuc15" "4800,898.15" "1" "1" "180")
(command "_insert" "blkuc15" "4800,898.89" "1" "1" "0")
(command "_insert" "blkuc15" "4800,898.52" "1" "1" "180")
(command "_insert" "blkuc15" "4800,899.26" "1" "1" "0")
(command "_insert" "blkuc15" "4800,898.89" "1" "1" "180")
(command "_insert" "blkuc15" "4800,899.63" "1" "1" "0")
(command "_insert" "blkuc15" "4800,899.26" "1" "1" "180")
(command "_insert" "blkuc15" "4800,900" "1" "1" "0")
(command "_insert" "blkuc15" "4800,899.63" "1" "1" "180")
(command "_insert" "blkuc15" "4800,900.37" "1" "1" "0")
(command "_insert" "blkuc15" "4800,900" "1" "1" "180")
(command "_insert" "blkuc15" "4800,900.74" "1" "1" "0")
(command "_insert" "blkuc15" "4800,900.37" "1" "1" "180")
(command "_insert" "blkuc15" "4800,901.11" "1" "1" "0")
(command "_insert" "blkuc15" "4800,900.74" "1" "1" "180")
(command "_insert" "blkuc15" "4800,901.48" "1" "1" "0")
(command "_insert" "blkuc15" "4800,901.11" "1" "1" "180")
(command "_insert" "blkuc15" "4800,901.85" "1" "1" "0")
(command "_insert" "blkuc15" "4800,901.48" "1" "1" "180")
(command "_insert" "blkuc15" "4800,902.22" "1" "1" "0")
(command "_insert" "blkuc15" "4800,901.85" "1" "1" "180")
(command "_insert" "blkuc15" "4800,902.59" "1" "1" "0")
(command "_insert" "blkuc15" "4800,902.22" "1" "1" "180")
(command "_insert" "blkuc15" "4800,902.96" "1" "1" "0")
(command "_insert" "blkuc15" "4800,902.59" "1" "1" "180")
(command "_insert" "blkuc15" "4800,903.33" "1" "1" "0")
(command "_insert" "blkuc15" "4800,902.96" "1" "1" "180")
(command "_insert" "blkuc15" "4800,903.7" "1" "1" "0")
(command "_insert" "blkuc15" "4800,903.33" "1" "1" "180")
(command "_insert" "blkuc15" "4800,904.07" "1" "1" "0")
(command "_insert" "blkuc15" "4800,903.7" "1" "1" "180")
(command "_insert" "blkuc15" "4800,904.44" "1" "1" "0")
(command "_insert" "blkuc15" "4800,904.07" "1" "1" "180")
(command "_insert" "blkuc15" "4800,904.81" "1" "1" "0")
(command "_insert" "blkuc15" "4800,904.44" "1" "1" "180")
(command "_insert" "blkuc15" "4800,905.18" "1" "1" "0")
(command "_insert" "blkuc15" "4800,904.81" "1" "1" "180")
(command "_insert" "blkuc15" "4800,905.55" "1" "1" "0")
(command "_insert" "blkuc15" "4800,905.18" "1" "1" "180")
(command "_insert" "blkuc15" "4800,905.92" "1" "1" "0")
(command "_insert" "blkuc15" "4800,905.55" "1" "1" "180")
(command "_insert" "blkuc15" "4800,906.29" "1" "1" "0")
(command "_insert" "blkuc15" "4800,905.92" "1" "1" "180")
(command "_insert" "blkuc15" "4800,906.66" "1" "1" "0")
(command "_insert" "blkuc15" "4800,906.29" "1" "1" "180")
(command "_insert" "blkuc15" "4800,907.03" "1" "1" "0")
(command "_insert" "blkuc15" "4800,906.66" "1" "1" "180")
(command "_insert" "blkuc15" "4800,907.4" "1" "1" "0")
(command "_insert" "blkuc15" "4800,907.03" "1" "1" "180")
(command "_insert" "blkuc15" "4800,907.77" "1" "1" "0")
(command "_insert" "blkuc15" "4800,907.4" "1" "1" "180")
(command "_insert" "blkuc15" "4800,908.14" "1" "1" "0")
(command "_insert" "blkuc15" "4800,907.77" "1" "1" "180")
(command "_insert" "blkuc15" "4800,908.51" "1" "1" "0")
(command "_insert" "blkuc15" "4800,908.14" "1" "1" "180")
(command "_insert" "blkuc15" "4800,908.88" "1" "1" "0")
(command "_insert" "blkuc15" "4800,908.51" "1" "1" "180")
(command "_insert" "blkuc15" "4800,909.25" "1" "1" "0")
(command "_insert" "blkuc15" "4800,908.88" "1" "1" "180")
(command "_insert" "blkuc15" "4800,909.62" "1" "1" "0")
(command "_insert" "blkuc15" "4800,909.25" "1" "1" "180")
(command "_insert" "blkuc15" "4800,909.99" "1" "1" "0")
(command "_insert" "blkuc15" "4800,909.62" "1" "1" "180")
(command "_insert" "blkuc15" "4800,910.36" "1" "1" "0")
(command "_insert" "blkuc15" "4800,909.99" "1" "1" "180")
(command "_insert" "blkuc15" "4800,910.73" "1" "1" "0")
(command "_insert" "blkuc15" "4800,910.36" "1" "1" "180")
(command "_insert" "blkuc15" "4800,911.1" "1" "1" "0")
(command "_insert" "blkuc15" "4800,910.73" "1" "1" "180")
(command "_insert" "blkuc15" "4800,911.47" "1" "1" "0")
(command "_insert" "blkuc15" "4800,911.1" "1" "1" "180")
(command "_insert" "blkuc15" "4800,911.84" "1" "1" "0")
(command "_insert" "blkuc15" "4800,911.47" "1" "1" "180")
(command "_insert" "blkuc15" "4800,912.21" "1" "1" "0")
(command "_insert" "blkuc15" "4800,911.84" "1" "1" "180")
(command "_insert" "blkuc15" "4800,912.58" "1" "1" "0")
(command "_insert" "blkuc15" "4800,912.21" "1" "1" "180")
(command "_insert" "blkuc15" "4800,912.95" "1" "1" "0")
(command "_insert" "blkuc15" "4800,912.58" "1" "1" "180")
(command "_insert" "blkuc15" "4800,913.32" "1" "1" "0")
(command "_insert" "blkuc15" "4800,912.95" "1" "1" "180")
(command "_insert" "blkuc15" "4800,913.69" "1" "1" "0")
(command "_insert" "blkuc15" "4800,913.32" "1" "1" "180")
(command "_insert" "blkuc15" "4800,914.06" "1" "1" "0")
(command "_insert" "blkuc15" "4800,913.69" "1" "1" "180")
(command "_insert" "blkuc15" "4800,914.43" "1" "1" "0")
(command "_insert" "blkuc15" "4800,914.06" "1" "1" "180")
(command "_insert" "blkuc15" "4800,914.8" "1" "1" "0")
(command "_insert" "blkuc15" "4800,914.43" "1" "1" "180")
(command "_insert" "blkuc15" "4800,915.17" "1" "1" "0")
(command "_insert" "blkuc15" "4800,914.8" "1" "1" "180")
(command "_insert" "blkuc15" "4800,915.54" "1" "1" "0")
(command "_insert" "blkuc15" "4800,915.17" "1" "1" "180")
(command "_insert" "blkuc15" "4800,915.91" "1" "1" "0")
(command "_insert" "blkuc15" "4800,915.54" "1" "1" "180")
(command "_insert" "blkuc15" "4800,916.28" "1" "1" "0")
(command "_insert" "blkuc15" "4800,915.91" "1" "1" "180")
(command "_insert" "blkuc15" "4800,916.65" "1" "1" "0")
(command "_insert" "blkuc15" "4800,916.28" "1" "1" "180")
(command "_insert" "blkuc15" "4800,917.02" "1" "1" "0")
(command "_insert" "blkuc15" "4800,916.65" "1" "1" "180")
(command "_insert" "blkuc15" "4800,917.39" "1" "1" "0")
(command "_insert" "blkuc15" "4800,917.02" "1" "1" "180")
(command "_insert" "blkuc15" "4800,917.76" "1" "1" "0")
(command "_insert" "blkuc15" "4800,917.39" "1" "1" "180")
(command "_insert" "blkuc15" "4800,918.13" "1" "1" "0")
(command "_insert" "blkuc15" "4800,917.76" "1" "1" "180")
(command "_insert" "blkuc15" "4800,918.5" "1" "1" "0")
(command "_insert" "blkuc15" "4800,918.13" "1" "1" "180")
(command "_insert" "blkuc15" "4800,918.87" "1" "1" "0")
(command "_insert" "blkuc15" "4800,918.5" "1" "1" "180")
(command "_insert" "blkuc15" "4800,919.24" "1" "1" "0")
(command "_insert" "blkuc15" "4800,918.87" "1" "1" "180")
(command "_insert" "blkuc15" "4800,919.61" "1" "1" "0")
(command "_insert" "blkuc15" "4800,919.24" "1" "1" "180")
(command "_insert" "blkuc15" "4800,919.98" "1" "1" "0")
(command "_insert" "blkuc15" "4800,919.61" "1" "1" "180")
(command "_insert" "blkuc15" "4800,920.35" "1" "1" "0")
(command "_insert" "blkuc15" "4800,919.98" "1" "1" "180")
(command "_insert" "blkuc15" "4800,920.72" "1" "1" "0")
(command "_insert" "blkuc15" "4800,920.35" "1" "1" "180")
(command "_insert" "blkuc15" "4800,921.09" "1" "1" "0")
(command "_insert" "blkuc15" "4800,920.72" "1" "1" "180")
(command "_insert" "blkuc15" "4800,921.46" "1" "1" "0")
(command "_insert" "blkuc15" "4800,921.09" "1" "1" "180")
(command "_insert" "blkuc15" "4800,921.83" "1" "1" "0")
(command "_insert" "blkuc15" "4800,921.46" "1" "1" "180")
(command "_insert" "blkuc15" "4800,922.2" "1" "1" "0")
(command "_insert" "blkuc15" "4800,921.83" "1" "1" "180")
(command "_insert" "blkuc15" "4800,922.57" "1" "1" "0")
(command "_insert" "blkuc15" "4800,922.2" "1" "1" "180")
(command "_insert" "blkuc15" "4800,922.94" "1" "1" "0")
(command "_insert" "blkuc15" "4800,922.57" "1" "1" "180")
(command "_insert" "blkuc15" "4800,923.31" "1" "1" "0")
(command "_insert" "blkuc15" "4800,922.94" "1" "1" "180")
(command "_insert" "blkuc15" "4800,923.68" "1" "1" "0")
(command "_insert" "blkuc15" "4800,923.31" "1" "1" "180")
(command "_insert" "blkuc15" "4800,924.05" "1" "1" "0")
(command "_insert" "blkuc15" "4800,923.68" "1" "1" "180")
(command "_insert" "blkuc15" "4800,924.42" "1" "1" "0")
(command "_insert" "blkuc15" "4800,924.05" "1" "1" "180")
(command "_insert" "blkuc15" "4800,924.79" "1" "1" "0")
(command "_insert" "blkuc15" "4800,924.42" "1" "1" "180")
(command "_insert" "blkuc15" "4800,925.16" "1" "1" "0")
(command "_insert" "blkuc15" "4800,924.79" "1" "1" "180")
(command "_insert" "blkuc15" "4800,925.53" "1" "1" "0")
(command "_insert" "blkuc15" "4800,925.16" "1" "1" "180")
(command "_insert" "blkuc15" "4800,925.9" "1" "1" "0")
(command "_insert" "blkuc15" "4800,925.53" "1" "1" "180")
(command "_insert" "blkuc15" "4800,926.27" "1" "1" "0")
(command "_insert" "blkuc15" "4800,925.9" "1" "1" "180")
(command "_insert" "blkuc15" "4800,926.64" "1" "1" "0")
(command "_insert" "blkuc15" "4800,926.27" "1" "1" "180")
(command "_insert" "blkuc15" "4800,927.01" "1" "1" "0")
(command "_insert" "blkuc15" "4800,926.64" "1" "1" "180")
(command "_insert" "blkuc15" "4800,927.38" "1" "1" "0")
(command "_insert" "blkuc15" "4800,927.01" "1" "1" "180")
(command "_insert" "blkuc15" "4800,927.75" "1" "1" "0")
(command "_insert" "blkuc15" "4800,927.38" "1" "1" "180")
(command "_layer" "set" "phccover" "")
(command "_rectangle" "4798.884,933.3" "4801.116,866.7")
(command "_layer" "set" "nitride" "")
(setq phc15 currobj)
(command "_layer" "set" "cover" "")
(command "_rectangle" "4798.884,836.7" "4801.116,963.3")
(command "_layer" "set" "nitride" "")
(command "_layer" "set" "text" "")
(command "_circle" "4797.934,846.7" "0.075")
(command "_circle" "4797.559,846.7" "0.15")
(command "_circle" "4797.184,846.7" "0.075")
(command "_circle" "4796.809,846.7" "0.15")
(command "_circle" "4797.934,848.7" "0.075")
(command "_circle" "4797.559,848.7" "0.075")
(command "_circle" "4797.184,848.7" "0.15")
(command "_circle" "4796.809,848.7" "0.15")
(command "_circle" "4797.934,850.7" "0.075")
(command "_circle" "4797.559,850.7" "0.15")
(command "_circle" "4797.184,850.7" "0.15")
(command "_circle" "4796.809,850.7" "0.15")
(command "_circle" "4797.934,852.7" "0.075")
(command "_circle" "4797.559,852.7" "0.075")
(command "_circle" "4797.184,852.7" "0.075")
(command "_circle" "4796.809,852.7" "0.075")
(command "_circle" "4796.434,852.7" "0.15")
(command "_circle" "4797.934,854.7" "0.075")
(command "_circle" "4797.559,854.7" "0.15")
(command "_circle" "4797.184,854.7" "0.075")
(command "_circle" "4796.809,854.7" "0.075")
(command "_circle" "4796.434,854.7" "0.15")
(command "_circle" "4797.934,856.7" "0.075")
(command "_circle" "4797.559,856.7" "0.075")
(command "_circle" "4797.184,856.7" "0.15")
(command "_circle" "4796.809,856.7" "0.075")
(command "_circle" "4796.434,856.7" "0.15")
(command "_circle" "4797.934,858.7" "0.075")
(command "_circle" "4797.559,858.7" "0.15")
(command "_circle" "4797.184,858.7" "0.15")
(command "_circle" "4796.809,858.7" "0.075")
(command "_circle" "4796.434,858.7" "0.15")
(command "_circle" "4797.934,860.7" "0.075")
(command "_circle" "4797.559,860.7" "0.075")
(command "_circle" "4797.184,860.7" "0.075")
(command "_circle" "4796.809,860.7" "0.15")
(command "_circle" "4796.434,860.7" "0.15")
(command "_circle" "4797.934,862.7" "0.075")
(command "_circle" "4797.559,862.7" "0.15")
(command "_circle" "4797.184,862.7" "0.075")
(command "_circle" "4796.809,862.7" "0.15")
(command "_circle" "4796.434,862.7" "0.15")
(command "_circle" "4797.934,864.7" "0.075")
(command "_circle" "4797.559,864.7" "0.075")
(command "_circle" "4797.184,864.7" "0.15")
(command "_circle" "4796.809,864.7" "0.15")
(command "_circle" "4796.434,864.7" "0.15")
(command "_circle" "4797.934,866.7" "0.075")
(command "_circle" "4797.559,866.7" "0.15")
(command "_circle" "4797.184,866.7" "0.15")
(command "_circle" "4796.809,866.7" "0.15")
(command "_circle" "4796.434,866.7" "0.15")
(command "_circle" "4797.934,868.7" "0.075")
(command "_circle" "4797.559,868.7" "0.075")
(command "_circle" "4797.184,868.7" "0.075")
(command "_circle" "4796.809,868.7" "0.075")
(command "_circle" "4796.434,868.7" "0.075")
(command "_circle" "4796.059,868.7" "0.15")
(command "_circle" "4797.934,870.7" "0.075")
(command "_circle" "4797.559,870.7" "0.15")
(command "_circle" "4797.184,870.7" "0.075")
(command "_circle" "4796.809,870.7" "0.075")
(command "_circle" "4796.434,870.7" "0.075")
(command "_circle" "4796.059,870.7" "0.15")
(command "_circle" "4797.934,872.7" "0.075")
(command "_circle" "4797.559,872.7" "0.075")
(command "_circle" "4797.184,872.7" "0.15")
(command "_circle" "4796.809,872.7" "0.075")
(command "_circle" "4796.434,872.7" "0.075")
(command "_circle" "4796.059,872.7" "0.15")
(command "_circle" "4797.934,874.7" "0.075")
(command "_circle" "4797.559,874.7" "0.15")
(command "_circle" "4797.184,874.7" "0.15")
(command "_circle" "4796.809,874.7" "0.075")
(command "_circle" "4796.434,874.7" "0.075")
(command "_circle" "4796.059,874.7" "0.15")
(command "_circle" "4797.934,876.7" "0.075")
(command "_circle" "4797.559,876.7" "0.075")
(command "_circle" "4797.184,876.7" "0.075")
(command "_circle" "4796.809,876.7" "0.15")
(command "_circle" "4796.434,876.7" "0.075")
(command "_circle" "4796.059,876.7" "0.15")
(command "_circle" "4797.934,878.7" "0.075")
(command "_circle" "4797.559,878.7" "0.15")
(command "_circle" "4797.184,878.7" "0.075")
(command "_circle" "4796.809,878.7" "0.15")
(command "_circle" "4796.434,878.7" "0.075")
(command "_circle" "4796.059,878.7" "0.15")
(command "_circle" "4797.934,880.7" "0.075")
(command "_circle" "4797.559,880.7" "0.075")
(command "_circle" "4797.184,880.7" "0.15")
(command "_circle" "4796.809,880.7" "0.15")
(command "_circle" "4796.434,880.7" "0.075")
(command "_circle" "4796.059,880.7" "0.15")
(command "_circle" "4797.934,882.7" "0.075")
(command "_circle" "4797.559,882.7" "0.15")
(command "_circle" "4797.184,882.7" "0.15")
(command "_circle" "4796.809,882.7" "0.15")
(command "_circle" "4796.434,882.7" "0.075")
(command "_circle" "4796.059,882.7" "0.15")
(command "_circle" "4797.934,884.7" "0.075")
(command "_circle" "4797.559,884.7" "0.075")
(command "_circle" "4797.184,884.7" "0.075")
(command "_circle" "4796.809,884.7" "0.075")
(command "_circle" "4796.434,884.7" "0.15")
(command "_circle" "4796.059,884.7" "0.15")
(command "_circle" "4797.934,886.7" "0.075")
(command "_circle" "4797.559,886.7" "0.15")
(command "_circle" "4797.184,886.7" "0.075")
(command "_circle" "4796.809,886.7" "0.075")
(command "_circle" "4796.434,886.7" "0.15")
(command "_circle" "4796.059,886.7" "0.15")
(command "_circle" "4797.934,888.7" "0.075")
(command "_circle" "4797.559,888.7" "0.075")
(command "_circle" "4797.184,888.7" "0.15")
(command "_circle" "4796.809,888.7" "0.075")
(command "_circle" "4796.434,888.7" "0.15")
(command "_circle" "4796.059,888.7" "0.15")
(command "_circle" "4797.934,890.7" "0.075")
(command "_circle" "4797.559,890.7" "0.15")
(command "_circle" "4797.184,890.7" "0.15")
(command "_circle" "4796.809,890.7" "0.075")
(command "_circle" "4796.434,890.7" "0.15")
(command "_circle" "4796.059,890.7" "0.15")
(command "_circle" "4797.934,892.7" "0.075")
(command "_circle" "4797.559,892.7" "0.075")
(command "_circle" "4797.184,892.7" "0.075")
(command "_circle" "4796.809,892.7" "0.15")
(command "_circle" "4796.434,892.7" "0.15")
(command "_circle" "4796.059,892.7" "0.15")
(command "_circle" "4797.934,894.7" "0.075")
(command "_circle" "4797.559,894.7" "0.15")
(command "_circle" "4797.184,894.7" "0.075")
(command "_circle" "4796.809,894.7" "0.15")
(command "_circle" "4796.434,894.7" "0.15")
(command "_circle" "4796.059,894.7" "0.15")
(command "_circle" "4797.934,896.7" "0.075")
(command "_circle" "4797.559,896.7" "0.075")
(command "_circle" "4797.184,896.7" "0.15")
(command "_circle" "4796.809,896.7" "0.15")
(command "_circle" "4796.434,896.7" "0.15")
(command "_circle" "4796.059,896.7" "0.15")
(command "_circle" "4797.934,898.7" "0.075")
(command "_circle" "4797.559,898.7" "0.15")
(command "_circle" "4797.184,898.7" "0.15")
(command "_circle" "4796.809,898.7" "0.15")
(command "_circle" "4796.434,898.7" "0.15")
(command "_circle" "4796.059,898.7" "0.15")
(command "_circle" "4797.934,900.7" "0.075")
(command "_circle" "4797.559,900.7" "0.075")
(command "_circle" "4797.184,900.7" "0.075")
(command "_circle" "4796.809,900.7" "0.075")
(command "_circle" "4796.434,900.7" "0.075")
(command "_circle" "4796.059,900.7" "0.075")
(command "_circle" "4795.684,900.7" "0.15")
(command "_circle" "4797.934,902.7" "0.075")
(command "_circle" "4797.559,902.7" "0.15")
(command "_circle" "4797.184,902.7" "0.075")
(command "_circle" "4796.809,902.7" "0.075")
(command "_circle" "4796.434,902.7" "0.075")
(command "_circle" "4796.059,902.7" "0.075")
(command "_circle" "4795.684,902.7" "0.15")
(command "_circle" "4797.934,904.7" "0.075")
(command "_circle" "4797.559,904.7" "0.075")
(command "_circle" "4797.184,904.7" "0.15")
(command "_circle" "4796.809,904.7" "0.075")
(command "_circle" "4796.434,904.7" "0.075")
(command "_circle" "4796.059,904.7" "0.075")
(command "_circle" "4795.684,904.7" "0.15")
(command "_circle" "4797.934,906.7" "0.075")
(command "_circle" "4797.559,906.7" "0.15")
(command "_circle" "4797.184,906.7" "0.15")
(command "_circle" "4796.809,906.7" "0.075")
(command "_circle" "4796.434,906.7" "0.075")
(command "_circle" "4796.059,906.7" "0.075")
(command "_circle" "4795.684,906.7" "0.15")
(command "_circle" "4797.934,908.7" "0.075")
(command "_circle" "4797.559,908.7" "0.075")
(command "_circle" "4797.184,908.7" "0.075")
(command "_circle" "4796.809,908.7" "0.15")
(command "_circle" "4796.434,908.7" "0.075")
(command "_circle" "4796.059,908.7" "0.075")
(command "_circle" "4795.684,908.7" "0.15")
(command "_circle" "4797.934,910.7" "0.075")
(command "_circle" "4797.559,910.7" "0.15")
(command "_circle" "4797.184,910.7" "0.075")
(command "_circle" "4796.809,910.7" "0.15")
(command "_circle" "4796.434,910.7" "0.075")
(command "_circle" "4796.059,910.7" "0.075")
(command "_circle" "4795.684,910.7" "0.15")
(command "_circle" "4797.934,912.7" "0.075")
(command "_circle" "4797.559,912.7" "0.075")
(command "_circle" "4797.184,912.7" "0.15")
(command "_circle" "4796.809,912.7" "0.15")
(command "_circle" "4796.434,912.7" "0.075")
(command "_circle" "4796.059,912.7" "0.075")
(command "_circle" "4795.684,912.7" "0.15")
(command "_circle" "4797.934,914.7" "0.075")
(command "_circle" "4797.559,914.7" "0.15")
(command "_circle" "4797.184,914.7" "0.15")
(command "_circle" "4796.809,914.7" "0.15")
(command "_circle" "4796.434,914.7" "0.075")
(command "_circle" "4796.059,914.7" "0.075")
(command "_circle" "4795.684,914.7" "0.15")
(command "_circle" "4797.934,916.7" "0.075")
(command "_circle" "4797.559,916.7" "0.075")
(command "_circle" "4797.184,916.7" "0.075")
(command "_circle" "4796.809,916.7" "0.075")
(command "_circle" "4796.434,916.7" "0.15")
(command "_circle" "4796.059,916.7" "0.075")
(command "_circle" "4795.684,916.7" "0.15")
(command "_circle" "4797.934,918.7" "0.075")
(command "_circle" "4797.559,918.7" "0.15")
(command "_circle" "4797.184,918.7" "0.075")
(command "_circle" "4796.809,918.7" "0.075")
(command "_circle" "4796.434,918.7" "0.15")
(command "_circle" "4796.059,918.7" "0.075")
(command "_circle" "4795.684,918.7" "0.15")
(command "_circle" "4797.934,920.7" "0.075")
(command "_circle" "4797.559,920.7" "0.075")
(command "_circle" "4797.184,920.7" "0.15")
(command "_circle" "4796.809,920.7" "0.075")
(command "_circle" "4796.434,920.7" "0.15")
(command "_circle" "4796.059,920.7" "0.075")
(command "_circle" "4795.684,920.7" "0.15")
(command "_circle" "4797.934,922.7" "0.075")
(command "_circle" "4797.559,922.7" "0.15")
(command "_circle" "4797.184,922.7" "0.15")
(command "_circle" "4796.809,922.7" "0.075")
(command "_circle" "4796.434,922.7" "0.15")
(command "_circle" "4796.059,922.7" "0.075")
(command "_circle" "4795.684,922.7" "0.15")
(command "_circle" "4797.934,924.7" "0.075")
(command "_circle" "4797.559,924.7" "0.075")
(command "_circle" "4797.184,924.7" "0.075")
(command "_circle" "4796.809,924.7" "0.15")
(command "_circle" "4796.434,924.7" "0.15")
(command "_circle" "4796.059,924.7" "0.075")
(command "_circle" "4795.684,924.7" "0.15")
(command "_circle" "4797.934,926.7" "0.075")
(command "_circle" "4797.559,926.7" "0.15")
(command "_circle" "4797.184,926.7" "0.075")
(command "_circle" "4796.809,926.7" "0.15")
(command "_circle" "4796.434,926.7" "0.15")
(command "_circle" "4796.059,926.7" "0.075")
(command "_circle" "4795.684,926.7" "0.15")
(command "_circle" "4797.934,928.7" "0.075")
(command "_circle" "4797.559,928.7" "0.075")
(command "_circle" "4797.184,928.7" "0.15")
(command "_circle" "4796.809,928.7" "0.15")
(command "_circle" "4796.434,928.7" "0.15")
(command "_circle" "4796.059,928.7" "0.075")
(command "_circle" "4795.684,928.7" "0.15")
(command "_circle" "4797.934,930.7" "0.075")
(command "_circle" "4797.559,930.7" "0.15")
(command "_circle" "4797.184,930.7" "0.15")
(command "_circle" "4796.809,930.7" "0.15")
(command "_circle" "4796.434,930.7" "0.15")
(command "_circle" "4796.059,930.7" "0.075")
(command "_circle" "4795.684,930.7" "0.15")
(command "_circle" "4797.934,932.7" "0.075")
(command "_circle" "4797.559,932.7" "0.075")
(command "_circle" "4797.184,932.7" "0.075")
(command "_circle" "4796.809,932.7" "0.075")
(command "_circle" "4796.434,932.7" "0.075")
(command "_circle" "4796.059,932.7" "0.15")
(command "_circle" "4795.684,932.7" "0.15")
(command "_circle" "4797.934,934.7" "0.075")
(command "_circle" "4797.559,934.7" "0.15")
(command "_circle" "4797.184,934.7" "0.075")
(command "_circle" "4796.809,934.7" "0.075")
(command "_circle" "4796.434,934.7" "0.075")
(command "_circle" "4796.059,934.7" "0.15")
(command "_circle" "4795.684,934.7" "0.15")
(command "_circle" "4797.934,936.7" "0.075")
(command "_circle" "4797.559,936.7" "0.075")
(command "_circle" "4797.184,936.7" "0.15")
(command "_circle" "4796.809,936.7" "0.075")
(command "_circle" "4796.434,936.7" "0.075")
(command "_circle" "4796.059,936.7" "0.15")
(command "_circle" "4795.684,936.7" "0.15")
(command "_circle" "4797.934,938.7" "0.075")
(command "_circle" "4797.559,938.7" "0.15")
(command "_circle" "4797.184,938.7" "0.15")
(command "_circle" "4796.809,938.7" "0.075")
(command "_circle" "4796.434,938.7" "0.075")
(command "_circle" "4796.059,938.7" "0.15")
(command "_circle" "4795.684,938.7" "0.15")
(command "_circle" "4797.934,940.7" "0.075")
(command "_circle" "4797.559,940.7" "0.075")
(command "_circle" "4797.184,940.7" "0.075")
(command "_circle" "4796.809,940.7" "0.15")
(command "_circle" "4796.434,940.7" "0.075")
(command "_circle" "4796.059,940.7" "0.15")
(command "_circle" "4795.684,940.7" "0.15")
(command "_circle" "4797.934,942.7" "0.075")
(command "_circle" "4797.559,942.7" "0.15")
(command "_circle" "4797.184,942.7" "0.075")
(command "_circle" "4796.809,942.7" "0.15")
(command "_circle" "4796.434,942.7" "0.075")
(command "_circle" "4796.059,942.7" "0.15")
(command "_circle" "4795.684,942.7" "0.15")
(command "_circle" "4797.934,944.7" "0.075")
(command "_circle" "4797.559,944.7" "0.075")
(command "_circle" "4797.184,944.7" "0.15")
(command "_circle" "4796.809,944.7" "0.15")
(command "_circle" "4796.434,944.7" "0.075")
(command "_circle" "4796.059,944.7" "0.15")
(command "_circle" "4795.684,944.7" "0.15")
(command "_circle" "4797.934,946.7" "0.075")
(command "_circle" "4797.559,946.7" "0.15")
(command "_circle" "4797.184,946.7" "0.15")
(command "_circle" "4796.809,946.7" "0.15")
(command "_circle" "4796.434,946.7" "0.075")
(command "_circle" "4796.059,946.7" "0.15")
(command "_circle" "4795.684,946.7" "0.15")
(command "_circle" "4797.934,948.7" "0.075")
(command "_circle" "4797.559,948.7" "0.075")
(command "_circle" "4797.184,948.7" "0.075")
(command "_circle" "4796.809,948.7" "0.075")
(command "_circle" "4796.434,948.7" "0.15")
(command "_circle" "4796.059,948.7" "0.15")
(command "_circle" "4795.684,948.7" "0.15")
(command "_circle" "4797.934,950.7" "0.075")
(command "_circle" "4797.559,950.7" "0.15")
(command "_circle" "4797.184,950.7" "0.075")
(command "_circle" "4796.809,950.7" "0.075")
(command "_circle" "4796.434,950.7" "0.15")
(command "_circle" "4796.059,950.7" "0.15")
(command "_circle" "4795.684,950.7" "0.15")
(command "_circle" "4797.934,952.7" "0.075")
(command "_circle" "4797.559,952.7" "0.075")
(command "_circle" "4797.184,952.7" "0.15")
(command "_circle" "4796.809,952.7" "0.075")
(command "_circle" "4796.434,952.7" "0.15")
(command "_circle" "4796.059,952.7" "0.15")
(command "_circle" "4795.684,952.7" "0.15")
(command "_circle" "4797.934,954.7" "0.075")
(command "_circle" "4797.559,954.7" "0.15")
(command "_circle" "4797.184,954.7" "0.15")
(command "_circle" "4796.809,954.7" "0.075")
(command "_circle" "4796.434,954.7" "0.15")
(command "_circle" "4796.059,954.7" "0.15")
(command "_circle" "4795.684,954.7" "0.15")
(command "_circle" "4797.934,956.7" "0.075")
(command "_circle" "4797.559,956.7" "0.075")
(command "_circle" "4797.184,956.7" "0.075")
(command "_circle" "4796.809,956.7" "0.15")
(command "_circle" "4796.434,956.7" "0.15")
(command "_circle" "4796.059,956.7" "0.15")
(command "_circle" "4795.684,956.7" "0.15")
(command "_circle" "4797.934,958.7" "0.075")
(command "_circle" "4797.559,958.7" "0.15")
(command "_circle" "4797.184,958.7" "0.075")
(command "_circle" "4796.809,958.7" "0.15")
(command "_circle" "4796.434,958.7" "0.15")
(command "_circle" "4796.059,958.7" "0.15")
(command "_circle" "4795.684,958.7" "0.15")
(command "_circle" "4797.934,960.7" "0.075")
(command "_circle" "4797.559,960.7" "0.075")
(command "_circle" "4797.184,960.7" "0.15")
(command "_circle" "4796.809,960.7" "0.15")
(command "_circle" "4796.434,960.7" "0.15")
(command "_circle" "4796.059,960.7" "0.15")
(command "_circle" "4795.684,960.7" "0.15")
(command "_circle" "4797.934,962.7" "0.075")
(command "_circle" "4797.559,962.7" "0.15")
(command "_circle" "4797.184,962.7" "0.15")
(command "_circle" "4796.809,962.7" "0.15")
(command "_circle" "4796.434,962.7" "0.15")
(command "_circle" "4796.059,962.7" "0.15")
(command "_circle" "4795.684,962.7" "0.15")
(command "_layer" "set" "nitride" "")
(command "_layer" "set" "text" "")
(command-s "_text" "4786.884,963.3" "2" "-90" "a = 370 nm" )
(sssetfirst nil (ssget "_L"))
(if (not (numberp (vl-string-search "Mac" (getvar "platform")))) (c:txtexp))
(command "_layer" "set" "nitride" "")
(command "_layer" "set" "text" "")
(command-s "_text" "4783.884,963.3" "2" "-90" "gap = 270 nm" )
(sssetfirst nil (ssget "_L"))
(if (not (numberp (vl-string-search "Mac" (getvar "platform")))) (c:txtexp))
(command "_layer" "set" "nitride" "")
(command "_layer" "set" "text" "")
(command-s "_text" "4780.884,963.3" "2" "-90" "amplitude = 132 nm" )
(sssetfirst nil (ssget "_L"))
(if (not (numberp (vl-string-search "Mac" (getvar "platform")))) (c:txtexp))
(command "_layer" "set" "nitride" "")
(command "_layer" "set" "text" "")
(command-s "_text" "4777.884,963.3" "2" "-90" "start width = 280 nm" )
(sssetfirst nil (ssget "_L"))
(if (not (numberp (vl-string-search "Mac" (getvar "platform")))) (c:txtexp))
(command "_layer" "set" "nitride" "")
(command "_layer" "set" "text" "")
(command-s "_text" "4774.884,963.3" "2" "-90" "width = 291 nm" )
(sssetfirst nil (ssget "_L"))
(if (not (numberp (vl-string-search "Mac" (getvar "platform")))) (c:txtexp))
(command "_layer" "set" "nitride" "")
(command "_layer" "set" "text" "")
(command-s "_text" "4771.884,963.3" "2" "-90" "taper: 15" )
(sssetfirst nil (ssget "_L"))
(if (not (numberp (vl-string-search "Mac" (getvar "platform")))) (c:txtexp))
(command "_layer" "set" "nitride" "")
(command "_layer" "set" "text" "")
(command-s "_text" "4768.884,963.3" "2" "-90" "nominal: 150" )
(sssetfirst nil (ssget "_L"))
(if (not (numberp (vl-string-search "Mac" (getvar "platform")))) (c:txtexp))
(command "_layer" "set" "nitride" "")
(command "_layer" "set" "indicators" "")
(setq coords (list 
(list 4720.415 940) 
(list 4720.415 920) 
(list 4700.415 900) 
(list 4720.415 880) 
(list 4720.415 860) 
(list 4720.415 900) 
(list 4720.415 887.0711) 
(list 4707.4861 900) 
(list 4720.415 912.9289) 
(list 4720.415 900)))
(apply 'command (append '("pline") coords '("c")))
(command "._fillet" "radius" "1" "._fillet" "P" (entlast))
(setq coords (list 
(list 4879.585 940) 
(list 4879.585 920) 
(list 4899.585 900) 
(list 4879.585 880) 
(list 4879.585 860) 
(list 4879.585 900) 
(list 4879.585 887.0711) 
(list 4892.5139 900) 
(list 4879.585 912.9289) 
(list 4879.585 900)))
(apply 'command (append '("pline") coords '("c")))
(command "._fillet" "radius" "1" "._fillet" "P" (entlast))
(command "_layer" "set" "holes" "")
(command "_circle" "4718.0629,914.1124" "0.5")
(command "_circle" "4715.7109,911.7603" "0.5")
(command "_circle" "4713.3588,909.4083" "0.5")
(command "_circle" "4711.0067,907.0562" "0.5")
(command "_circle" "4708.6547,904.7041" "0.5")
(command "_circle" "4706.3026,902.3521" "0.5")
(command "_circle" "4703.9505,900" "0.5")
(command "_circle" "4706.3026,897.6479" "0.5")
(command "_circle" "4708.6547,895.2959" "0.5")
(command "_circle" "4711.0067,892.9438" "0.5")
(command "_circle" "4713.3588,890.5917" "0.5")
(command "_circle" "4715.7109,888.2397" "0.5")
(command "_circle" "4718.0629,885.8876" "0.5")
(command "_circle" "4881.9371,914.1124" "0.5")
(command "_circle" "4884.2891,911.7603" "0.5")
(command "_circle" "4886.6412,909.4083" "0.5")
(command "_circle" "4888.9933,907.0562" "0.5")
(command "_circle" "4891.3453,904.7041" "0.5")
(command "_circle" "4893.6974,902.3521" "0.5")
(command "_circle" "4896.0495,900" "0.5")
(command "_circle" "4893.6974,897.6479" "0.5")
(command "_circle" "4891.3453,895.2959" "0.5")
(command "_circle" "4888.9933,892.9438" "0.5")
(command "_circle" "4886.6412,890.5917" "0.5")
(command "_circle" "4884.2891,888.2397" "0.5")
(command "_circle" "4881.9371,885.8876" "0.5")
(command "_layer" "set" "nitride" "")
(command "_block" "blkcoupler15" "4800,900" coupler15 "")
(command "_insert" "blkcoupler15" "4800,900" "1" "1" "0")
(command "_insert" "blkcoupler15" "4800,900" "1" "1" "180")
(command "_block" "blksinglenanobeam15" "4800,900" singlenanobeam15 "")
(command "_insert" "blksinglenanobeam15" "4800,900" "1" "1" "0")
(command "_insert" "blksinglenanobeam15" "4800,900" "1" "1" "180")
(command "_block" "blkanglednodearray15" "4800,900" anglednodearray15 "")
(command "_insert" "blkanglednodearray15" "4800,900" "1" "1" "0")
(command "_insert" "blkanglednodearray15" "4800,900" "1" "1" "180")
(command "_block" "blkcooledsinglenanobeam15" "4800,900" cooledsinglenanobeam15 "")
(command "_insert" "blkcooledsinglenanobeam15" "4800,900" "1" "1" "0")
(command "_insert" "blkcooledsinglenanobeam15" "4800,900" "1" "1" "180")
(command "_block" "blkyjunction15" "4800,900" yjunction15 "")
(command "_insert" "blkyjunction15" "4800,900" "1" "1" "0")
(command "_insert" "blkyjunction15" "4800,900" "1" "1" "180")
; DRAWING BULGING VEE GROOVE
(command "_layer" "set" "vgroove" "")
(setq coords (list 
(list 4725.415 -605) 
(list 4725.415 0) 
(list 4725.415 0) 
(list 4725.415 1800) 
(list 4725.415 1800) 
(list 4725.415 2405) 
(list 4874.585 2405) 
(list 4874.585 1800) 
(list 4874.585 1800) 
(list 4874.585 0) 
(list 4874.585 0) 
(list 4874.585 -605)))
(apply 'command (append '("pline") coords '("c")))
(command "._fillet" "radius" "0" "._fillet" "P" (entlast))
(command "_layer" "set" "window" "")
(command "_rectangle" "4725.415,-1935" "4874.585,-600")
(command "_rectangle" "4725.415,2400" "4874.585,5300")
(command "_layer" "set" "grid" "")
(command "_rectangle" "4726.415,-1934" "4749.9433,-1909.2133")
(command "_array" "last" "" "R" "75" "3" "25.7867" "24.5283")
(command "_rectangle" "4801,-1934" "4824.5283,-1909.2133")
(command "_array" "last" "" "R" "75" "3" "25.7867" "24.5283")
(command "_rectangle" "4726.415,1" "4749.9433,25.7")
(command "_array" "last" "" "R" "70" "3" "25.7" "24.5283")
(command "_rectangle" "4801,1" "4824.5283,25.7")
(command "_array" "last" "" "R" "70" "3" "25.7" "24.5283")
(command "_rectangle" "4726.415,1801" "4749.9433,1825.9185")
(command "_array" "last" "" "R" "135" "3" "25.9185" "24.5283")
(command "_rectangle" "4801,1801" "4824.5283,1825.9185")
(command "_array" "last" "" "R" "135" "3" "25.9185" "24.5283")
(command "_layer" "set" "vgrooveFDA" "")
(command "_rectangle" "4874.585,-2233" "4725.415,-1933")
(command "_layer" "set" "nitride" "")
(command "_layer" "set" "holes" "")
(command "_circle" "4877.085,331.5" "0.5")
(command "_array" "last" "" "R" "379" "1" "3" "2.5")
(command "_circle" "4722.915,331.5" "0.5")
(command "_array" "last" "" "R" "379" "1" "3" "-2.5")
(command "_layer" "set" "nitride" "")
(command "_layer" "set" "window" "")
(command "_layer" "set" "window" "")
(command "_rectangle" "4879.585,0" "5040.415,1800")
(command "._fillet" "radius" "20" "._fillet" "P" (entlast))
(command "_layer" "set" "grid" "")
(command "_rectangle" "4880.585,1" "4902.4179,25.7")
(command "_array" "last" "" "R" "70" "7" "25.7" "22.8329")
(command "_layer" "set" "nitride" "")
; DRAWING REGION LAYER
(command "_layer" "set" "regionLayer15" "")
(command "_rectangle" "4720,-460" "4880,2260")
(command "_layer" "set" "nitride" "")
(setq coupler15 nil)
(setq singlenanobeam15 nil)
(setq anglednodearray15 nil)
(setq cooledsinglenanobeam15 nil)
(setq yjunction15 nil)
; DEVICE #16
(command "_layer" "set" "window" "")
(command "_circle" "5032.915,-415" "5")
(command "_circle" "5032.915,-402.5" "5")
(command "_circle" "5032.915,-390" "5")
(command "_circle" "5032.915,-377.5" "5")
(command "_circle" "5020.415,-415" "5")
(command "_circle" "5020.415,-402.5" "5")
(command "_circle" "5020.415,-390" "5")
(command "_circle" "5020.415,-377.5" "5")
(command "_circle" "5007.915,-415" "5")
(command "_circle" "5007.915,-402.5" "5")
(command "_circle" "5007.915,-390" "5")
(command "_circle" "5007.915,-377.5" "5")
(command "_circle" "4995.415,-415" "5")
(command "_circle" "4995.415,-402.5" "5")
(command "_circle" "4995.415,-390" "5")
(command "_circle" "4995.415,-377.5" "5")
(command "_layer" "set" "nitride" "")
(setq currobj nil)
(setq currobj (ssadd))
; DRAWING COUPLER
(setq coords (list 
(list 5120.0695 -415) 
(list 5120.0695 -413) 
(list 5193.585 -413) 
(list 5193.585 -413) 
(list 5193.9677 -413.0761) 
(list 5194.2921 -413.2929) 
(list 5194.5089 -413.6173) 
(list 5194.585 -414) 
(list 5194.585 -411.8) 
(list 5194.585 -411.8) 
(list 5194.5089 -412.1827) 
(list 5194.2921 -412.5071) 
(list 5193.9677 -412.7239) 
(list 5193.585 -412.8) 
(list 5120.0695 -412.8) 
(list 5120.0695 -410.8) 
(list 5119.9305 -410.8) 
(list 5119.9305 -412.8) 
(list 5046.415 -412.8) 
(list 5046.0323 -412.7239) 
(list 5045.7079 -412.5071) 
(list 5045.4911 -412.1827) 
(list 5045.415 -411.8) 
(list 5045.415 -411.8) 
(list 5045.415 -414) 
(list 5045.4911 -413.6173) 
(list 5045.7079 -413.2929) 
(list 5046.0323 -413.0761) 
(list 5046.415 -413) 
(list 5046.415 -413) 
(list 5119.9305 -413) 
(list 5119.9305 -415)))
(apply 'command (append '("pline") coords '("c")))
(setq currobj (ssadd (entlast) currobj))
(command "._fillet" "radius" "0.3" "._fillet" "P" (entlast))
(command "_layer" "set" "holes" "")
(command "_circle" "5120,-412.9" "0.113")
(setq currobj (ssadd (entlast) currobj))
(command "_layer" "set" "nitride" "")
(command "_layer" "set" "text" "")
(command "_circle" "5119.2,-415" "0.075")
(command "_circle" "5119.2,-414.7" "0.075")
(command "_circle" "5119.2,-414.4" "0.075")
(command "_circle" "5118.9,-415" "0.075")
(command "_circle" "5118.9,-414.7" "0.075")
(command "_circle" "5118.9,-414.4" "0.075")
(command "_circle" "5118.6,-415" "0.075")
(command "_circle" "5118.6,-414.7" "0.075")
(command "_circle" "5118.6,-414.4" "0.075")
(command "_layer" "set" "nitride" "")
(command "_layer" "set" "prebias" "")
(command "_rectangle" "5045.415,-414" "5194.585,-411.8")
(setq currobj (ssadd (entlast) currobj))
(command "_rectangle" "5119.9305,-415" "5120.0695,-410.8")
(setq currobj (ssadd (entlast) currobj))
(command "_layer" "set" "nitride" "")
(setq coupler16 currobj)
(setq currobj nil)
(setq currobj (ssadd))
; DRAWING SINGLE NANOBEAM
(setq coords (list 
(list 5120.0695 -410.8) 
(list 5120.0695 -409.1417) 
(list 5120.0695 -407.4833) 
(list 5120.0695 -405.825) 
(list 5120.0695 -404.1667) 
(list 5120.0695 -402.5083) 
(list 5120.0695 -400.85) 
(list 5120.0695 -399.1917) 
(list 5120.0695 -397.5333) 
(list 5120.0695 -395.875) 
(list 5120.0696 -394.2167) 
(list 5120.0696 -392.5583) 
(list 5120.0696 -390.9) 
(list 5120.0696 -389.2417) 
(list 5120.0697 -387.5833) 
(list 5120.0697 -385.925) 
(list 5120.0698 -384.2667) 
(list 5120.0698 -382.6083) 
(list 5120.0699 -380.95) 
(list 5120.07 -379.2917) 
(list 5120.07 -377.6333) 
(list 5120.0701 -375.975) 
(list 5120.0702 -374.3167) 
(list 5120.0703 -372.6583) 
(list 5120.0704 -371) 
(list 5120.0705 -369.3417) 
(list 5120.0707 -367.6833) 
(list 5120.0708 -366.025) 
(list 5120.071 -364.3667) 
(list 5120.0711 -362.7083) 
(list 5120.0713 -361.05) 
(list 5120.0715 -359.3917) 
(list 5120.0717 -357.7333) 
(list 5120.0719 -356.075) 
(list 5120.0721 -354.4167) 
(list 5120.0724 -352.7583) 
(list 5120.0726 -351.1) 
(list 5120.0729 -349.4417) 
(list 5120.0732 -347.7833) 
(list 5120.0735 -346.125) 
(list 5120.0738 -344.4667) 
(list 5120.0741 -342.8083) 
(list 5120.0745 -341.15) 
(list 5120.0748 -339.4917) 
(list 5120.0752 -337.8333) 
(list 5120.0756 -336.175) 
(list 5120.076 -334.5167) 
(list 5120.0764 -332.8583) 
(list 5120.0769 -331.2) 
(list 5120.0774 -329.5417) 
(list 5120.0779 -327.8833) 
(list 5120.0784 -326.225) 
(list 5120.0789 -324.5667) 
(list 5120.0795 -322.9083) 
(list 5120.08 -321.25) 
(list 5120.0806 -319.5917) 
(list 5120.0812 -317.9333) 
(list 5120.0819 -316.275) 
(list 5120.0825 -314.6167) 
(list 5120.0832 -312.9583) 
(list 5120.0839 -311.3) 
(list 5120.0847 -309.6417) 
(list 5120.0854 -307.9833) 
(list 5120.0862 -306.325) 
(list 5120.087 -304.6667) 
(list 5120.0879 -303.0083) 
(list 5120.0887 -301.35) 
(list 5120.0896 -299.6917) 
(list 5120.0905 -298.0333) 
(list 5120.0915 -296.375) 
(list 5120.0924 -294.7167) 
(list 5120.0934 -293.0583) 
(list 5120.0944 -291.4) 
(list 5120.0955 -289.7417) 
(list 5120.0966 -288.0833) 
(list 5120.0977 -286.425) 
(list 5120.0988 -284.7667) 
(list 5120.1 -283.1083) 
(list 5120.1012 -281.45) 
(list 5120.1025 -279.7917) 
(list 5120.1037 -278.1333) 
(list 5120.105 -276.475) 
(list 5120.1064 -274.8167) 
(list 5120.1077 -273.1583) 
(list 5120.1091 -271.5) 
(list 5120.1105 -269.8417) 
(list 5120.112 -268.1833) 
(list 5120.1135 -266.525) 
(list 5120.1151 -264.8667) 
(list 5120.1166 -263.2083) 
(list 5120.1182 -261.55) 
(list 5120.1199 -259.8917) 
(list 5120.1215 -258.2333) 
(list 5120.1233 -256.575) 
(list 5120.125 -254.9167) 
(list 5120.1268 -253.2583) 
(list 5120.1286 -251.6) 
(list 5120.1305 -249.9417) 
(list 5120.1324 -248.2833) 
(list 5120.1344 -246.625) 
(list 5120.1363 -244.9667) 
(list 5120.1384 -243.3083) 
(list 5120.1404 -241.65) 
(list 5120.1425 -239.9917) 
(list 5120.1447 -238.3333) 
(list 5120.1469 -236.675) 
(list 5120.1491 -235.0167) 
(list 5120.1514 -233.3583) 
(list 5120.1537 -231.7) 
(list 5120.1561 -230.0417) 
(list 5120.1585 -228.3833) 
(list 5120.1609 -226.725) 
(list 5120.1634 -225.0667) 
(list 5120.1659 -223.4083) 
(list 5120.1685 -221.75) 
(list 5120.1712 -220.0917) 
(list 5120.1738 -218.4333) 
(list 5120.1766 -216.775) 
(list 5120.1793 -215.1167) 
(list 5120.1821 -213.4583) 
(list 5120.185 -211.8) 
(list 5119.815 -211.8) 
(list 5119.8179 -213.4583) 
(list 5119.8207 -215.1167) 
(list 5119.8234 -216.775) 
(list 5119.8262 -218.4333) 
(list 5119.8288 -220.0917) 
(list 5119.8315 -221.75) 
(list 5119.8341 -223.4083) 
(list 5119.8366 -225.0667) 
(list 5119.8391 -226.725) 
(list 5119.8415 -228.3833) 
(list 5119.8439 -230.0417) 
(list 5119.8463 -231.7) 
(list 5119.8486 -233.3583) 
(list 5119.8509 -235.0167) 
(list 5119.8531 -236.675) 
(list 5119.8553 -238.3333) 
(list 5119.8575 -239.9917) 
(list 5119.8596 -241.65) 
(list 5119.8616 -243.3083) 
(list 5119.8637 -244.9667) 
(list 5119.8656 -246.625) 
(list 5119.8676 -248.2833) 
(list 5119.8695 -249.9417) 
(list 5119.8714 -251.6) 
(list 5119.8732 -253.2583) 
(list 5119.875 -254.9167) 
(list 5119.8767 -256.575) 
(list 5119.8785 -258.2333) 
(list 5119.8801 -259.8917) 
(list 5119.8818 -261.55) 
(list 5119.8834 -263.2083) 
(list 5119.8849 -264.8667) 
(list 5119.8865 -266.525) 
(list 5119.888 -268.1833) 
(list 5119.8895 -269.8417) 
(list 5119.8909 -271.5) 
(list 5119.8923 -273.1583) 
(list 5119.8936 -274.8167) 
(list 5119.895 -276.475) 
(list 5119.8963 -278.1333) 
(list 5119.8975 -279.7917) 
(list 5119.8988 -281.45) 
(list 5119.9 -283.1083) 
(list 5119.9012 -284.7667) 
(list 5119.9023 -286.425) 
(list 5119.9034 -288.0833) 
(list 5119.9045 -289.7417) 
(list 5119.9056 -291.4) 
(list 5119.9066 -293.0583) 
(list 5119.9076 -294.7167) 
(list 5119.9085 -296.375) 
(list 5119.9095 -298.0333) 
(list 5119.9104 -299.6917) 
(list 5119.9113 -301.35) 
(list 5119.9121 -303.0083) 
(list 5119.913 -304.6667) 
(list 5119.9138 -306.325) 
(list 5119.9146 -307.9833) 
(list 5119.9153 -309.6417) 
(list 5119.9161 -311.3) 
(list 5119.9168 -312.9583) 
(list 5119.9175 -314.6167) 
(list 5119.9181 -316.275) 
(list 5119.9188 -317.9333) 
(list 5119.9194 -319.5917) 
(list 5119.92 -321.25) 
(list 5119.9205 -322.9083) 
(list 5119.9211 -324.5667) 
(list 5119.9216 -326.225) 
(list 5119.9221 -327.8833) 
(list 5119.9226 -329.5417) 
(list 5119.9231 -331.2) 
(list 5119.9236 -332.8583) 
(list 5119.924 -334.5167) 
(list 5119.9244 -336.175) 
(list 5119.9248 -337.8333) 
(list 5119.9252 -339.4917) 
(list 5119.9255 -341.15) 
(list 5119.9259 -342.8083) 
(list 5119.9262 -344.4667) 
(list 5119.9265 -346.125) 
(list 5119.9268 -347.7833) 
(list 5119.9271 -349.4417) 
(list 5119.9274 -351.1) 
(list 5119.9276 -352.7583) 
(list 5119.9279 -354.4167) 
(list 5119.9281 -356.075) 
(list 5119.9283 -357.7333) 
(list 5119.9285 -359.3917) 
(list 5119.9287 -361.05) 
(list 5119.9289 -362.7083) 
(list 5119.929 -364.3667) 
(list 5119.9292 -366.025) 
(list 5119.9293 -367.6833) 
(list 5119.9295 -369.3417) 
(list 5119.9296 -371) 
(list 5119.9297 -372.6583) 
(list 5119.9298 -374.3167) 
(list 5119.9299 -375.975) 
(list 5119.93 -377.6333) 
(list 5119.93 -379.2917) 
(list 5119.9301 -380.95) 
(list 5119.9302 -382.6083) 
(list 5119.9302 -384.2667) 
(list 5119.9303 -385.925) 
(list 5119.9303 -387.5833) 
(list 5119.9304 -389.2417) 
(list 5119.9304 -390.9) 
(list 5119.9304 -392.5583) 
(list 5119.9304 -394.2167) 
(list 5119.9305 -395.875) 
(list 5119.9305 -397.5333) 
(list 5119.9305 -399.1917) 
(list 5119.9305 -400.85) 
(list 5119.9305 -402.5083) 
(list 5119.9305 -404.1667) 
(list 5119.9305 -405.825) 
(list 5119.9305 -407.4833) 
(list 5119.9305 -409.1417) 
(list 5119.9305 -410.8)))
(apply 'command (append '("pline") coords '("c")))
(setq currobj (ssadd (entlast) currobj))
(command "_layer" "set" "prebias" "")
(command "_rectangle" "5119.815,-410.8" "5120.185,-211.8")
(setq currobj (ssadd (entlast) currobj))
(command "_layer" "set" "nitride" "")
(setq singlenanobeam16 currobj)
(setq currobj nil)
(setq currobj (ssadd))
; DRAWING NODE ARRAY
(setq coords (list 
(list 5120.185 -211.8) 
(list 5120.5625 -201.8) 
(list 5120.5625 -201.8) 
(list 5120.5625 -200.8) 
(list 5194.585 -212.6864) 
(list 5194.585 -207.7434) 
(list 5120.5625 -197.357) 
(list 5120.5625 -196.357) 
(list 5120.5625 -196.357) 
(list 5120.2625 -186.357) 
(list 5119.7375 -186.357) 
(list 5119.4375 -196.357) 
(list 5119.4375 -196.357) 
(list 5119.4375 -197.357) 
(list 5045.415 -207.7434) 
(list 5045.415 -212.6864) 
(list 5119.4375 -200.8) 
(list 5119.4375 -201.8) 
(list 5119.4375 -201.8) 
(list 5119.815 -211.8)))
(apply 'command (append '("pline") coords '("c")))
(setq currobj (ssadd (entlast) currobj))
(command "_layer" "set" "prebias" "")
(setq coords (list 
(list 5119.4375 -212.6864) 
(list 5119.4375 -200.8) 
(list 5045.415 -212.6864) 
(list 5045.415 -207.7434) 
(list 5119.4375 -197.357) 
(list 5119.4375 -186.357) 
(list 5120.5625 -186.357) 
(list 5120.5625 -197.357) 
(list 5194.585 -207.7434) 
(list 5194.585 -212.6864) 
(list 5120.5625 -200.8) 
(list 5120.5625 -212.6864)))
(apply 'command (append '("pline") coords '("c")))
(setq currobj (ssadd (entlast) currobj))
(command "_layer" "set" "nitride" "")
(command "_layer" "set" "fda1" "")
(setq coords (list 
(list 5120.5625 -200.657) 
(list 5194.585 -212.5434) 
(list 5194.585 -212.3664) 
(list 5120.5625 -200.58)))
(apply 'command (append '("pline") coords '("c")))
(setq currobj (ssadd (entlast) currobj))
(setq coords (list 
(list 5120.5625 -200.437) 
(list 5194.585 -212.2234) 
(list 5194.585 -212.0464) 
(list 5120.5625 -200.36)))
(apply 'command (append '("pline") coords '("c")))
(setq currobj (ssadd (entlast) currobj))
(setq coords (list 
(list 5120.5625 -200.217) 
(list 5194.585 -211.9034) 
(list 5194.585 -211.7264) 
(list 5120.5625 -200.14)))
(apply 'command (append '("pline") coords '("c")))
(setq currobj (ssadd (entlast) currobj))
(setq coords (list 
(list 5120.5625 -199.997) 
(list 5194.585 -211.5834) 
(list 5194.585 -211.4064) 
(list 5120.5625 -199.92)))
(apply 'command (append '("pline") coords '("c")))
(setq currobj (ssadd (entlast) currobj))
(setq coords (list 
(list 5120.5625 -199.777) 
(list 5194.585 -211.2634) 
(list 5194.585 -211.0864) 
(list 5120.5625 -199.7)))
(apply 'command (append '("pline") coords '("c")))
(setq currobj (ssadd (entlast) currobj))
(setq coords (list 
(list 5120.5625 -199.557) 
(list 5194.585 -210.9434) 
(list 5194.585 -210.7664) 
(list 5120.5625 -199.48)))
(apply 'command (append '("pline") coords '("c")))
(setq currobj (ssadd (entlast) currobj))
(setq coords (list 
(list 5120.5625 -199.337) 
(list 5194.585 -210.6234) 
(list 5194.585 -210.4464) 
(list 5120.5625 -199.26)))
(apply 'command (append '("pline") coords '("c")))
(setq currobj (ssadd (entlast) currobj))
(setq coords (list 
(list 5120.5625 -199.117) 
(list 5194.585 -210.3034) 
(list 5194.585 -210.1264) 
(list 5120.5625 -199.04)))
(apply 'command (append '("pline") coords '("c")))
(setq currobj (ssadd (entlast) currobj))
(setq coords (list 
(list 5120.5625 -198.897) 
(list 5194.585 -209.9834) 
(list 5194.585 -209.8064) 
(list 5120.5625 -198.82)))
(apply 'command (append '("pline") coords '("c")))
(setq currobj (ssadd (entlast) currobj))
(setq coords (list 
(list 5120.5625 -198.677) 
(list 5194.585 -209.6634) 
(list 5194.585 -209.4864) 
(list 5120.5625 -198.6)))
(apply 'command (append '("pline") coords '("c")))
(setq currobj (ssadd (entlast) currobj))
(setq coords (list 
(list 5120.5625 -198.457) 
(list 5194.585 -209.3434) 
(list 5194.585 -209.1664) 
(list 5120.5625 -198.38)))
(apply 'command (append '("pline") coords '("c")))
(setq currobj (ssadd (entlast) currobj))
(setq coords (list 
(list 5120.5625 -198.237) 
(list 5194.585 -209.0234) 
(list 5194.585 -208.8464) 
(list 5120.5625 -198.16)))
(apply 'command (append '("pline") coords '("c")))
(setq currobj (ssadd (entlast) currobj))
(setq coords (list 
(list 5120.5625 -198.017) 
(list 5194.585 -208.7034) 
(list 5194.585 -208.5264) 
(list 5120.5625 -197.94)))
(apply 'command (append '("pline") coords '("c")))
(setq currobj (ssadd (entlast) currobj))
(setq coords (list 
(list 5120.5625 -197.797) 
(list 5194.585 -208.3834) 
(list 5194.585 -208.2064) 
(list 5120.5625 -197.72)))
(apply 'command (append '("pline") coords '("c")))
(setq currobj (ssadd (entlast) currobj))
(setq coords (list 
(list 5120.5625 -197.577) 
(list 5194.585 -208.0634) 
(list 5194.585 -207.8864) 
(list 5120.5625 -197.5)))
(apply 'command (append '("pline") coords '("c")))
(setq currobj (ssadd (entlast) currobj))
(setq coords (list 
(list 5119.4375 -197.5) 
(list 5045.415 -207.8864) 
(list 5045.415 -208.0634) 
(list 5119.4375 -197.577)))
(apply 'command (append '("pline") coords '("c")))
(setq currobj (ssadd (entlast) currobj))
(setq coords (list 
(list 5119.4375 -197.72) 
(list 5045.415 -208.2064) 
(list 5045.415 -208.3834) 
(list 5119.4375 -197.797)))
(apply 'command (append '("pline") coords '("c")))
(setq currobj (ssadd (entlast) currobj))
(setq coords (list 
(list 5119.4375 -197.94) 
(list 5045.415 -208.5264) 
(list 5045.415 -208.7034) 
(list 5119.4375 -198.017)))
(apply 'command (append '("pline") coords '("c")))
(setq currobj (ssadd (entlast) currobj))
(setq coords (list 
(list 5119.4375 -198.16) 
(list 5045.415 -208.8464) 
(list 5045.415 -209.0234) 
(list 5119.4375 -198.237)))
(apply 'command (append '("pline") coords '("c")))
(setq currobj (ssadd (entlast) currobj))
(setq coords (list 
(list 5119.4375 -198.38) 
(list 5045.415 -209.1664) 
(list 5045.415 -209.3434) 
(list 5119.4375 -198.457)))
(apply 'command (append '("pline") coords '("c")))
(setq currobj (ssadd (entlast) currobj))
(setq coords (list 
(list 5119.4375 -198.6) 
(list 5045.415 -209.4864) 
(list 5045.415 -209.6634) 
(list 5119.4375 -198.677)))
(apply 'command (append '("pline") coords '("c")))
(setq currobj (ssadd (entlast) currobj))
(setq coords (list 
(list 5119.4375 -198.82) 
(list 5045.415 -209.8064) 
(list 5045.415 -209.9834) 
(list 5119.4375 -198.897)))
(apply 'command (append '("pline") coords '("c")))
(setq currobj (ssadd (entlast) currobj))
(setq coords (list 
(list 5119.4375 -199.04) 
(list 5045.415 -210.1264) 
(list 5045.415 -210.3034) 
(list 5119.4375 -199.117)))
(apply 'command (append '("pline") coords '("c")))
(setq currobj (ssadd (entlast) currobj))
(setq coords (list 
(list 5119.4375 -199.26) 
(list 5045.415 -210.4464) 
(list 5045.415 -210.6234) 
(list 5119.4375 -199.337)))
(apply 'command (append '("pline") coords '("c")))
(setq currobj (ssadd (entlast) currobj))
(setq coords (list 
(list 5119.4375 -199.48) 
(list 5045.415 -210.7664) 
(list 5045.415 -210.9434) 
(list 5119.4375 -199.557)))
(apply 'command (append '("pline") coords '("c")))
(setq currobj (ssadd (entlast) currobj))
(setq coords (list 
(list 5119.4375 -199.7) 
(list 5045.415 -211.0864) 
(list 5045.415 -211.2634) 
(list 5119.4375 -199.777)))
(apply 'command (append '("pline") coords '("c")))
(setq currobj (ssadd (entlast) currobj))
(setq coords (list 
(list 5119.4375 -199.92) 
(list 5045.415 -211.4064) 
(list 5045.415 -211.5834) 
(list 5119.4375 -199.997)))
(apply 'command (append '("pline") coords '("c")))
(setq currobj (ssadd (entlast) currobj))
(setq coords (list 
(list 5119.4375 -200.14) 
(list 5045.415 -211.7264) 
(list 5045.415 -211.9034) 
(list 5119.4375 -200.217)))
(apply 'command (append '("pline") coords '("c")))
(setq currobj (ssadd (entlast) currobj))
(setq coords (list 
(list 5119.4375 -200.36) 
(list 5045.415 -212.0464) 
(list 5045.415 -212.2234) 
(list 5119.4375 -200.437)))
(apply 'command (append '("pline") coords '("c")))
(setq currobj (ssadd (entlast) currobj))
(setq coords (list 
(list 5119.4375 -200.58) 
(list 5045.415 -212.3664) 
(list 5045.415 -212.5434) 
(list 5119.4375 -200.657)))
(apply 'command (append '("pline") coords '("c")))
(setq currobj (ssadd (entlast) currobj))
(command "_layer" "set" "nitride" "")
(command "_layer" "set" "text" "")
(command "_circle" "5118.985,-211.8" "0.075")
(command "_circle" "5118.985,-211.5" "0.075")
(command "_circle" "5118.985,-211.2" "0.075")
(command "_circle" "5118.985,-210.9" "0.075")
(command "_circle" "5118.985,-210.6" "0.075")
(command "_circle" "5118.685,-211.8" "0.075")
(command "_circle" "5118.685,-211.5" "0.075")
(command "_circle" "5118.685,-211.2" "0.075")
(command "_circle" "5118.685,-210.9" "0.075")
(command "_circle" "5118.685,-210.6" "0.075")
(command "_circle" "5118.385,-211.8" "0.075")
(command "_circle" "5118.385,-211.5" "0.075")
(command "_circle" "5118.385,-211.2" "0.075")
(command "_circle" "5118.385,-210.9" "0.075")
(command "_circle" "5118.385,-210.6" "0.075")
(command "_circle" "5118.085,-211.8" "0.075")
(command "_circle" "5118.085,-211.5" "0.075")
(command "_circle" "5118.085,-211.2" "0.075")
(command "_circle" "5118.085,-210.9" "0.075")
(command "_circle" "5118.085,-210.6" "0.075")
(command "_circle" "5117.785,-211.8" "0.075")
(command "_circle" "5117.785,-211.5" "0.075")
(command "_circle" "5117.785,-211.2" "0.075")
(command "_circle" "5117.785,-210.9" "0.075")
(command "_circle" "5117.785,-210.6" "0.075")
(command "_layer" "set" "nitride" "")
(setq anglednodearray16 currobj)
(setq currobj nil)
(setq currobj (ssadd))
; DRAWING COOLED SINGLE NANOBEAM
(setq coords (list 
(list 5120.2625 -186.357) 
(list 5120.2625 -181.357) 
(list 5119.7375 -181.357) 
(list 5119.7375 -186.357)))
(apply 'command (append '("pline") coords '("c")))
(setq currobj (ssadd (entlast) currobj))
(command "_layer" "set" "prebias" "")
(command "_rectangle" "5119.7375,-186.357" "5120.2625,-181.357")
(setq currobj (ssadd (entlast) currobj))
(command "_layer" "set" "nitride" "")
(setq coords (list 
(list 5120.2625 -181.357) 
(list 5120.5625 -171.357) 
(list 5120.5625 -171.357) 
(list 5120.5625 -170.357) 
(list 5194.585 -171.107) 
(list 5194.585 -166.164) 
(list 5120.5625 -166.914) 
(list 5120.5625 -165.914) 
(list 5120.5625 -165.914) 
(list 5120.2625 -155.914) 
(list 5119.7375 -155.914) 
(list 5119.4375 -165.914) 
(list 5119.4375 -165.914) 
(list 5119.4375 -166.914) 
(list 5045.415 -166.164) 
(list 5045.415 -171.107) 
(list 5119.4375 -170.357) 
(list 5119.4375 -171.357) 
(list 5119.4375 -171.357) 
(list 5119.7375 -181.357)))
(apply 'command (append '("pline") coords '("c")))
(setq currobj (ssadd (entlast) currobj))
(command "_layer" "set" "prebias" "")
(setq coords (list 
(list 5119.4375 -181.357) 
(list 5119.4375 -170.357) 
(list 5045.415 -171.107) 
(list 5045.415 -166.164) 
(list 5119.4375 -166.914) 
(list 5119.4375 -155.914) 
(list 5120.5625 -155.914) 
(list 5120.5625 -166.914) 
(list 5194.585 -166.164) 
(list 5194.585 -171.107) 
(list 5120.5625 -170.357) 
(list 5120.5625 -181.357)))
(apply 'command (append '("pline") coords '("c")))
(setq currobj (ssadd (entlast) currobj))
(command "_layer" "set" "nitride" "")
(command "_layer" "set" "fda1" "")
(setq coords (list 
(list 5120.5625 -170.214) 
(list 5194.585 -170.964) 
(list 5194.585 -170.787) 
(list 5120.5625 -170.137)))
(apply 'command (append '("pline") coords '("c")))
(setq currobj (ssadd (entlast) currobj))
(setq coords (list 
(list 5120.5625 -169.994) 
(list 5194.585 -170.644) 
(list 5194.585 -170.467) 
(list 5120.5625 -169.917)))
(apply 'command (append '("pline") coords '("c")))
(setq currobj (ssadd (entlast) currobj))
(setq coords (list 
(list 5120.5625 -169.774) 
(list 5194.585 -170.324) 
(list 5194.585 -170.147) 
(list 5120.5625 -169.697)))
(apply 'command (append '("pline") coords '("c")))
(setq currobj (ssadd (entlast) currobj))
(setq coords (list 
(list 5120.5625 -169.554) 
(list 5194.585 -170.004) 
(list 5194.585 -169.827) 
(list 5120.5625 -169.477)))
(apply 'command (append '("pline") coords '("c")))
(setq currobj (ssadd (entlast) currobj))
(setq coords (list 
(list 5120.5625 -169.334) 
(list 5194.585 -169.684) 
(list 5194.585 -169.507) 
(list 5120.5625 -169.257)))
(apply 'command (append '("pline") coords '("c")))
(setq currobj (ssadd (entlast) currobj))
(setq coords (list 
(list 5120.5625 -169.114) 
(list 5194.585 -169.364) 
(list 5194.585 -169.187) 
(list 5120.5625 -169.037)))
(apply 'command (append '("pline") coords '("c")))
(setq currobj (ssadd (entlast) currobj))
(setq coords (list 
(list 5120.5625 -168.894) 
(list 5194.585 -169.044) 
(list 5194.585 -168.867) 
(list 5120.5625 -168.817)))
(apply 'command (append '("pline") coords '("c")))
(setq currobj (ssadd (entlast) currobj))
(setq coords (list 
(list 5120.5625 -168.674) 
(list 5194.585 -168.724) 
(list 5194.585 -168.547) 
(list 5120.5625 -168.597)))
(apply 'command (append '("pline") coords '("c")))
(setq currobj (ssadd (entlast) currobj))
(setq coords (list 
(list 5120.5625 -168.454) 
(list 5194.585 -168.404) 
(list 5194.585 -168.227) 
(list 5120.5625 -168.377)))
(apply 'command (append '("pline") coords '("c")))
(setq currobj (ssadd (entlast) currobj))
(setq coords (list 
(list 5120.5625 -168.234) 
(list 5194.585 -168.084) 
(list 5194.585 -167.907) 
(list 5120.5625 -168.157)))
(apply 'command (append '("pline") coords '("c")))
(setq currobj (ssadd (entlast) currobj))
(setq coords (list 
(list 5120.5625 -168.014) 
(list 5194.585 -167.764) 
(list 5194.585 -167.587) 
(list 5120.5625 -167.937)))
(apply 'command (append '("pline") coords '("c")))
(setq currobj (ssadd (entlast) currobj))
(setq coords (list 
(list 5120.5625 -167.794) 
(list 5194.585 -167.444) 
(list 5194.585 -167.267) 
(list 5120.5625 -167.717)))
(apply 'command (append '("pline") coords '("c")))
(setq currobj (ssadd (entlast) currobj))
(setq coords (list 
(list 5120.5625 -167.574) 
(list 5194.585 -167.124) 
(list 5194.585 -166.947) 
(list 5120.5625 -167.497)))
(apply 'command (append '("pline") coords '("c")))
(setq currobj (ssadd (entlast) currobj))
(setq coords (list 
(list 5120.5625 -167.354) 
(list 5194.585 -166.804) 
(list 5194.585 -166.627) 
(list 5120.5625 -167.277)))
(apply 'command (append '("pline") coords '("c")))
(setq currobj (ssadd (entlast) currobj))
(setq coords (list 
(list 5120.5625 -167.134) 
(list 5194.585 -166.484) 
(list 5194.585 -166.307) 
(list 5120.5625 -167.057)))
(apply 'command (append '("pline") coords '("c")))
(setq currobj (ssadd (entlast) currobj))
(setq coords (list 
(list 5119.4375 -167.057) 
(list 5045.415 -166.307) 
(list 5045.415 -166.484) 
(list 5119.4375 -167.134)))
(apply 'command (append '("pline") coords '("c")))
(setq currobj (ssadd (entlast) currobj))
(setq coords (list 
(list 5119.4375 -167.277) 
(list 5045.415 -166.627) 
(list 5045.415 -166.804) 
(list 5119.4375 -167.354)))
(apply 'command (append '("pline") coords '("c")))
(setq currobj (ssadd (entlast) currobj))
(setq coords (list 
(list 5119.4375 -167.497) 
(list 5045.415 -166.947) 
(list 5045.415 -167.124) 
(list 5119.4375 -167.574)))
(apply 'command (append '("pline") coords '("c")))
(setq currobj (ssadd (entlast) currobj))
(setq coords (list 
(list 5119.4375 -167.717) 
(list 5045.415 -167.267) 
(list 5045.415 -167.444) 
(list 5119.4375 -167.794)))
(apply 'command (append '("pline") coords '("c")))
(setq currobj (ssadd (entlast) currobj))
(setq coords (list 
(list 5119.4375 -167.937) 
(list 5045.415 -167.587) 
(list 5045.415 -167.764) 
(list 5119.4375 -168.014)))
(apply 'command (append '("pline") coords '("c")))
(setq currobj (ssadd (entlast) currobj))
(setq coords (list 
(list 5119.4375 -168.157) 
(list 5045.415 -167.907) 
(list 5045.415 -168.084) 
(list 5119.4375 -168.234)))
(apply 'command (append '("pline") coords '("c")))
(setq currobj (ssadd (entlast) currobj))
(setq coords (list 
(list 5119.4375 -168.377) 
(list 5045.415 -168.227) 
(list 5045.415 -168.404) 
(list 5119.4375 -168.454)))
(apply 'command (append '("pline") coords '("c")))
(setq currobj (ssadd (entlast) currobj))
(setq coords (list 
(list 5119.4375 -168.597) 
(list 5045.415 -168.547) 
(list 5045.415 -168.724) 
(list 5119.4375 -168.674)))
(apply 'command (append '("pline") coords '("c")))
(setq currobj (ssadd (entlast) currobj))
(setq coords (list 
(list 5119.4375 -168.817) 
(list 5045.415 -168.867) 
(list 5045.415 -169.044) 
(list 5119.4375 -168.894)))
(apply 'command (append '("pline") coords '("c")))
(setq currobj (ssadd (entlast) currobj))
(setq coords (list 
(list 5119.4375 -169.037) 
(list 5045.415 -169.187) 
(list 5045.415 -169.364) 
(list 5119.4375 -169.114)))
(apply 'command (append '("pline") coords '("c")))
(setq currobj (ssadd (entlast) currobj))
(setq coords (list 
(list 5119.4375 -169.257) 
(list 5045.415 -169.507) 
(list 5045.415 -169.684) 
(list 5119.4375 -169.334)))
(apply 'command (append '("pline") coords '("c")))
(setq currobj (ssadd (entlast) currobj))
(setq coords (list 
(list 5119.4375 -169.477) 
(list 5045.415 -169.827) 
(list 5045.415 -170.004) 
(list 5119.4375 -169.554)))
(apply 'command (append '("pline") coords '("c")))
(setq currobj (ssadd (entlast) currobj))
(setq coords (list 
(list 5119.4375 -169.697) 
(list 5045.415 -170.147) 
(list 5045.415 -170.324) 
(list 5119.4375 -169.774)))
(apply 'command (append '("pline") coords '("c")))
(setq currobj (ssadd (entlast) currobj))
(setq coords (list 
(list 5119.4375 -169.917) 
(list 5045.415 -170.467) 
(list 5045.415 -170.644) 
(list 5119.4375 -169.994)))
(apply 'command (append '("pline") coords '("c")))
(setq currobj (ssadd (entlast) currobj))
(setq coords (list 
(list 5119.4375 -170.137) 
(list 5045.415 -170.787) 
(list 5045.415 -170.964) 
(list 5119.4375 -170.214)))
(apply 'command (append '("pline") coords '("c")))
(setq currobj (ssadd (entlast) currobj))
(command "_layer" "set" "nitride" "")
(command "_layer" "set" "text" "")
(command "_circle" "5119.0625,-181.357" "0.075")
(command "_circle" "5119.0625,-181.057" "0.075")
(command "_circle" "5119.0625,-180.757" "0.075")
(command "_circle" "5119.0625,-180.457" "0.075")
(command "_circle" "5119.0625,-180.157" "0.075")
(command "_circle" "5118.7625,-181.357" "0.075")
(command "_circle" "5118.7625,-181.057" "0.075")
(command "_circle" "5118.7625,-180.757" "0.075")
(command "_circle" "5118.7625,-180.457" "0.075")
(command "_circle" "5118.7625,-180.157" "0.075")
(command "_circle" "5118.4625,-181.357" "0.075")
(command "_circle" "5118.4625,-181.057" "0.075")
(command "_circle" "5118.4625,-180.757" "0.075")
(command "_circle" "5118.4625,-180.457" "0.075")
(command "_circle" "5118.4625,-180.157" "0.075")
(command "_circle" "5118.1625,-181.357" "0.075")
(command "_circle" "5118.1625,-181.057" "0.075")
(command "_circle" "5118.1625,-180.757" "0.075")
(command "_circle" "5118.1625,-180.457" "0.075")
(command "_circle" "5118.1625,-180.157" "0.075")
(command "_circle" "5117.8625,-181.357" "0.075")
(command "_circle" "5117.8625,-181.057" "0.075")
(command "_circle" "5117.8625,-180.757" "0.075")
(command "_circle" "5117.8625,-180.457" "0.075")
(command "_circle" "5117.8625,-180.157" "0.075")
(command "_layer" "set" "nitride" "")
(setq coords (list 
(list 5120.2625 -155.914) 
(list 5120.2625 -40.2693) 
(list 5119.7375 -40.2693) 
(list 5119.7375 -155.914)))
(apply 'command (append '("pline") coords '("c")))
(setq currobj (ssadd (entlast) currobj))
(command "_layer" "set" "prebias" "")
(command "_rectangle" "5119.7375,-155.914" "5120.2625,-40.2693")
(setq currobj (ssadd (entlast) currobj))
(command "_layer" "set" "nitride" "")
(setq coords (list 
(list 5120.2625 -40.2693) 
(list 5120.5625 -30.2693) 
(list 5120.5625 -30.2693) 
(list 5120.5625 -29.2693) 
(list 5194.585 -30.0193) 
(list 5194.585 -25.0763) 
(list 5120.5625 -25.8263) 
(list 5120.5625 -24.8263) 
(list 5120.5625 -24.8263) 
(list 5120.2625 -14.8263) 
(list 5119.7375 -14.8263) 
(list 5119.4375 -24.8263) 
(list 5119.4375 -24.8263) 
(list 5119.4375 -25.8263) 
(list 5045.415 -25.0763) 
(list 5045.415 -30.0193) 
(list 5119.4375 -29.2693) 
(list 5119.4375 -30.2693) 
(list 5119.4375 -30.2693) 
(list 5119.7375 -40.2693)))
(apply 'command (append '("pline") coords '("c")))
(setq currobj (ssadd (entlast) currobj))
(command "_layer" "set" "prebias" "")
(setq coords (list 
(list 5119.4375 -40.2693) 
(list 5119.4375 -29.2693) 
(list 5045.415 -30.0193) 
(list 5045.415 -25.0763) 
(list 5119.4375 -25.8263) 
(list 5119.4375 -14.8263) 
(list 5120.5625 -14.8263) 
(list 5120.5625 -25.8263) 
(list 5194.585 -25.0763) 
(list 5194.585 -30.0193) 
(list 5120.5625 -29.2693) 
(list 5120.5625 -40.2693)))
(apply 'command (append '("pline") coords '("c")))
(setq currobj (ssadd (entlast) currobj))
(command "_layer" "set" "nitride" "")
(command "_layer" "set" "fda1" "")
(setq coords (list 
(list 5120.5625 -29.1263) 
(list 5194.585 -29.8763) 
(list 5194.585 -29.6993) 
(list 5120.5625 -29.0493)))
(apply 'command (append '("pline") coords '("c")))
(setq currobj (ssadd (entlast) currobj))
(setq coords (list 
(list 5120.5625 -28.9063) 
(list 5194.585 -29.5563) 
(list 5194.585 -29.3793) 
(list 5120.5625 -28.8293)))
(apply 'command (append '("pline") coords '("c")))
(setq currobj (ssadd (entlast) currobj))
(setq coords (list 
(list 5120.5625 -28.6863) 
(list 5194.585 -29.2363) 
(list 5194.585 -29.0593) 
(list 5120.5625 -28.6093)))
(apply 'command (append '("pline") coords '("c")))
(setq currobj (ssadd (entlast) currobj))
(setq coords (list 
(list 5120.5625 -28.4663) 
(list 5194.585 -28.9163) 
(list 5194.585 -28.7393) 
(list 5120.5625 -28.3893)))
(apply 'command (append '("pline") coords '("c")))
(setq currobj (ssadd (entlast) currobj))
(setq coords (list 
(list 5120.5625 -28.2463) 
(list 5194.585 -28.5963) 
(list 5194.585 -28.4193) 
(list 5120.5625 -28.1693)))
(apply 'command (append '("pline") coords '("c")))
(setq currobj (ssadd (entlast) currobj))
(setq coords (list 
(list 5120.5625 -28.0263) 
(list 5194.585 -28.2763) 
(list 5194.585 -28.0993) 
(list 5120.5625 -27.9493)))
(apply 'command (append '("pline") coords '("c")))
(setq currobj (ssadd (entlast) currobj))
(setq coords (list 
(list 5120.5625 -27.8063) 
(list 5194.585 -27.9563) 
(list 5194.585 -27.7793) 
(list 5120.5625 -27.7293)))
(apply 'command (append '("pline") coords '("c")))
(setq currobj (ssadd (entlast) currobj))
(setq coords (list 
(list 5120.5625 -27.5863) 
(list 5194.585 -27.6363) 
(list 5194.585 -27.4593) 
(list 5120.5625 -27.5093)))
(apply 'command (append '("pline") coords '("c")))
(setq currobj (ssadd (entlast) currobj))
(setq coords (list 
(list 5120.5625 -27.3663) 
(list 5194.585 -27.3163) 
(list 5194.585 -27.1393) 
(list 5120.5625 -27.2893)))
(apply 'command (append '("pline") coords '("c")))
(setq currobj (ssadd (entlast) currobj))
(setq coords (list 
(list 5120.5625 -27.1463) 
(list 5194.585 -26.9963) 
(list 5194.585 -26.8193) 
(list 5120.5625 -27.0693)))
(apply 'command (append '("pline") coords '("c")))
(setq currobj (ssadd (entlast) currobj))
(setq coords (list 
(list 5120.5625 -26.9263) 
(list 5194.585 -26.6763) 
(list 5194.585 -26.4993) 
(list 5120.5625 -26.8493)))
(apply 'command (append '("pline") coords '("c")))
(setq currobj (ssadd (entlast) currobj))
(setq coords (list 
(list 5120.5625 -26.7063) 
(list 5194.585 -26.3563) 
(list 5194.585 -26.1793) 
(list 5120.5625 -26.6293)))
(apply 'command (append '("pline") coords '("c")))
(setq currobj (ssadd (entlast) currobj))
(setq coords (list 
(list 5120.5625 -26.4863) 
(list 5194.585 -26.0363) 
(list 5194.585 -25.8593) 
(list 5120.5625 -26.4093)))
(apply 'command (append '("pline") coords '("c")))
(setq currobj (ssadd (entlast) currobj))
(setq coords (list 
(list 5120.5625 -26.2663) 
(list 5194.585 -25.7163) 
(list 5194.585 -25.5393) 
(list 5120.5625 -26.1893)))
(apply 'command (append '("pline") coords '("c")))
(setq currobj (ssadd (entlast) currobj))
(setq coords (list 
(list 5120.5625 -26.0463) 
(list 5194.585 -25.3963) 
(list 5194.585 -25.2193) 
(list 5120.5625 -25.9693)))
(apply 'command (append '("pline") coords '("c")))
(setq currobj (ssadd (entlast) currobj))
(setq coords (list 
(list 5119.4375 -25.9693) 
(list 5045.415 -25.2193) 
(list 5045.415 -25.3963) 
(list 5119.4375 -26.0463)))
(apply 'command (append '("pline") coords '("c")))
(setq currobj (ssadd (entlast) currobj))
(setq coords (list 
(list 5119.4375 -26.1893) 
(list 5045.415 -25.5393) 
(list 5045.415 -25.7163) 
(list 5119.4375 -26.2663)))
(apply 'command (append '("pline") coords '("c")))
(setq currobj (ssadd (entlast) currobj))
(setq coords (list 
(list 5119.4375 -26.4093) 
(list 5045.415 -25.8593) 
(list 5045.415 -26.0363) 
(list 5119.4375 -26.4863)))
(apply 'command (append '("pline") coords '("c")))
(setq currobj (ssadd (entlast) currobj))
(setq coords (list 
(list 5119.4375 -26.6293) 
(list 5045.415 -26.1793) 
(list 5045.415 -26.3563) 
(list 5119.4375 -26.7063)))
(apply 'command (append '("pline") coords '("c")))
(setq currobj (ssadd (entlast) currobj))
(setq coords (list 
(list 5119.4375 -26.8493) 
(list 5045.415 -26.4993) 
(list 5045.415 -26.6763) 
(list 5119.4375 -26.9263)))
(apply 'command (append '("pline") coords '("c")))
(setq currobj (ssadd (entlast) currobj))
(setq coords (list 
(list 5119.4375 -27.0693) 
(list 5045.415 -26.8193) 
(list 5045.415 -26.9963) 
(list 5119.4375 -27.1463)))
(apply 'command (append '("pline") coords '("c")))
(setq currobj (ssadd (entlast) currobj))
(setq coords (list 
(list 5119.4375 -27.2893) 
(list 5045.415 -27.1393) 
(list 5045.415 -27.3163) 
(list 5119.4375 -27.3663)))
(apply 'command (append '("pline") coords '("c")))
(setq currobj (ssadd (entlast) currobj))
(setq coords (list 
(list 5119.4375 -27.5093) 
(list 5045.415 -27.4593) 
(list 5045.415 -27.6363) 
(list 5119.4375 -27.5863)))
(apply 'command (append '("pline") coords '("c")))
(setq currobj (ssadd (entlast) currobj))
(setq coords (list 
(list 5119.4375 -27.7293) 
(list 5045.415 -27.7793) 
(list 5045.415 -27.9563) 
(list 5119.4375 -27.8063)))
(apply 'command (append '("pline") coords '("c")))
(setq currobj (ssadd (entlast) currobj))
(setq coords (list 
(list 5119.4375 -27.9493) 
(list 5045.415 -28.0993) 
(list 5045.415 -28.2763) 
(list 5119.4375 -28.0263)))
(apply 'command (append '("pline") coords '("c")))
(setq currobj (ssadd (entlast) currobj))
(setq coords (list 
(list 5119.4375 -28.1693) 
(list 5045.415 -28.4193) 
(list 5045.415 -28.5963) 
(list 5119.4375 -28.2463)))
(apply 'command (append '("pline") coords '("c")))
(setq currobj (ssadd (entlast) currobj))
(setq coords (list 
(list 5119.4375 -28.3893) 
(list 5045.415 -28.7393) 
(list 5045.415 -28.9163) 
(list 5119.4375 -28.4663)))
(apply 'command (append '("pline") coords '("c")))
(setq currobj (ssadd (entlast) currobj))
(setq coords (list 
(list 5119.4375 -28.6093) 
(list 5045.415 -29.0593) 
(list 5045.415 -29.2363) 
(list 5119.4375 -28.6863)))
(apply 'command (append '("pline") coords '("c")))
(setq currobj (ssadd (entlast) currobj))
(setq coords (list 
(list 5119.4375 -28.8293) 
(list 5045.415 -29.3793) 
(list 5045.415 -29.5563) 
(list 5119.4375 -28.9063)))
(apply 'command (append '("pline") coords '("c")))
(setq currobj (ssadd (entlast) currobj))
(setq coords (list 
(list 5119.4375 -29.0493) 
(list 5045.415 -29.6993) 
(list 5045.415 -29.8763) 
(list 5119.4375 -29.1263)))
(apply 'command (append '("pline") coords '("c")))
(setq currobj (ssadd (entlast) currobj))
(command "_layer" "set" "nitride" "")
(command "_layer" "set" "text" "")
(command "_circle" "5119.0625,-40.2693" "0.075")
(command "_circle" "5119.0625,-39.9693" "0.075")
(command "_circle" "5119.0625,-39.6693" "0.075")
(command "_circle" "5119.0625,-39.3693" "0.075")
(command "_circle" "5119.0625,-39.0693" "0.075")
(command "_circle" "5118.7625,-40.2693" "0.075")
(command "_circle" "5118.7625,-39.9693" "0.075")
(command "_circle" "5118.7625,-39.6693" "0.075")
(command "_circle" "5118.7625,-39.3693" "0.075")
(command "_circle" "5118.7625,-39.0693" "0.075")
(command "_circle" "5118.4625,-40.2693" "0.075")
(command "_circle" "5118.4625,-39.9693" "0.075")
(command "_circle" "5118.4625,-39.6693" "0.075")
(command "_circle" "5118.4625,-39.3693" "0.075")
(command "_circle" "5118.4625,-39.0693" "0.075")
(command "_circle" "5118.1625,-40.2693" "0.075")
(command "_circle" "5118.1625,-39.9693" "0.075")
(command "_circle" "5118.1625,-39.6693" "0.075")
(command "_circle" "5118.1625,-39.3693" "0.075")
(command "_circle" "5118.1625,-39.0693" "0.075")
(command "_circle" "5117.8625,-40.2693" "0.075")
(command "_circle" "5117.8625,-39.9693" "0.075")
(command "_circle" "5117.8625,-39.6693" "0.075")
(command "_circle" "5117.8625,-39.3693" "0.075")
(command "_circle" "5117.8625,-39.0693" "0.075")
(command "_layer" "set" "nitride" "")
(setq coords (list 
(list 5120.2625 -14.8263) 
(list 5120.2625 100.8184) 
(list 5119.7375 100.8184) 
(list 5119.7375 -14.8263)))
(apply 'command (append '("pline") coords '("c")))
(setq currobj (ssadd (entlast) currobj))
(command "_layer" "set" "prebias" "")
(command "_rectangle" "5119.7375,-14.8263" "5120.2625,100.8184")
(setq currobj (ssadd (entlast) currobj))
(command "_layer" "set" "nitride" "")
(setq coords (list 
(list 5120.2625 100.8184) 
(list 5120.5625 110.8184) 
(list 5120.5625 110.8184) 
(list 5120.5625 111.8184) 
(list 5194.585 111.0684) 
(list 5194.585 116.0114) 
(list 5120.5625 115.2614) 
(list 5120.5625 116.2614) 
(list 5120.5625 116.2614) 
(list 5120.2625 126.2614) 
(list 5119.7375 126.2614) 
(list 5119.4375 116.2614) 
(list 5119.4375 116.2614) 
(list 5119.4375 115.2614) 
(list 5045.415 116.0114) 
(list 5045.415 111.0684) 
(list 5119.4375 111.8184) 
(list 5119.4375 110.8184) 
(list 5119.4375 110.8184) 
(list 5119.7375 100.8184)))
(apply 'command (append '("pline") coords '("c")))
(setq currobj (ssadd (entlast) currobj))
(command "_layer" "set" "prebias" "")
(setq coords (list 
(list 5119.4375 100.8184) 
(list 5119.4375 111.8184) 
(list 5045.415 111.0684) 
(list 5045.415 116.0114) 
(list 5119.4375 115.2614) 
(list 5119.4375 126.2614) 
(list 5120.5625 126.2614) 
(list 5120.5625 115.2614) 
(list 5194.585 116.0114) 
(list 5194.585 111.0684) 
(list 5120.5625 111.8184) 
(list 5120.5625 100.8184)))
(apply 'command (append '("pline") coords '("c")))
(setq currobj (ssadd (entlast) currobj))
(command "_layer" "set" "nitride" "")
(command "_layer" "set" "fda1" "")
(setq coords (list 
(list 5120.5625 111.9614) 
(list 5194.585 111.2114) 
(list 5194.585 111.3884) 
(list 5120.5625 112.0384)))
(apply 'command (append '("pline") coords '("c")))
(setq currobj (ssadd (entlast) currobj))
(setq coords (list 
(list 5120.5625 112.1814) 
(list 5194.585 111.5314) 
(list 5194.585 111.7084) 
(list 5120.5625 112.2584)))
(apply 'command (append '("pline") coords '("c")))
(setq currobj (ssadd (entlast) currobj))
(setq coords (list 
(list 5120.5625 112.4014) 
(list 5194.585 111.8514) 
(list 5194.585 112.0284) 
(list 5120.5625 112.4784)))
(apply 'command (append '("pline") coords '("c")))
(setq currobj (ssadd (entlast) currobj))
(setq coords (list 
(list 5120.5625 112.6214) 
(list 5194.585 112.1714) 
(list 5194.585 112.3484) 
(list 5120.5625 112.6984)))
(apply 'command (append '("pline") coords '("c")))
(setq currobj (ssadd (entlast) currobj))
(setq coords (list 
(list 5120.5625 112.8414) 
(list 5194.585 112.4914) 
(list 5194.585 112.6684) 
(list 5120.5625 112.9184)))
(apply 'command (append '("pline") coords '("c")))
(setq currobj (ssadd (entlast) currobj))
(setq coords (list 
(list 5120.5625 113.0614) 
(list 5194.585 112.8114) 
(list 5194.585 112.9884) 
(list 5120.5625 113.1384)))
(apply 'command (append '("pline") coords '("c")))
(setq currobj (ssadd (entlast) currobj))
(setq coords (list 
(list 5120.5625 113.2814) 
(list 5194.585 113.1314) 
(list 5194.585 113.3084) 
(list 5120.5625 113.3584)))
(apply 'command (append '("pline") coords '("c")))
(setq currobj (ssadd (entlast) currobj))
(setq coords (list 
(list 5120.5625 113.5014) 
(list 5194.585 113.4514) 
(list 5194.585 113.6284) 
(list 5120.5625 113.5784)))
(apply 'command (append '("pline") coords '("c")))
(setq currobj (ssadd (entlast) currobj))
(setq coords (list 
(list 5120.5625 113.7214) 
(list 5194.585 113.7714) 
(list 5194.585 113.9484) 
(list 5120.5625 113.7984)))
(apply 'command (append '("pline") coords '("c")))
(setq currobj (ssadd (entlast) currobj))
(setq coords (list 
(list 5120.5625 113.9414) 
(list 5194.585 114.0914) 
(list 5194.585 114.2684) 
(list 5120.5625 114.0184)))
(apply 'command (append '("pline") coords '("c")))
(setq currobj (ssadd (entlast) currobj))
(setq coords (list 
(list 5120.5625 114.1614) 
(list 5194.585 114.4114) 
(list 5194.585 114.5884) 
(list 5120.5625 114.2384)))
(apply 'command (append '("pline") coords '("c")))
(setq currobj (ssadd (entlast) currobj))
(setq coords (list 
(list 5120.5625 114.3814) 
(list 5194.585 114.7314) 
(list 5194.585 114.9084) 
(list 5120.5625 114.4584)))
(apply 'command (append '("pline") coords '("c")))
(setq currobj (ssadd (entlast) currobj))
(setq coords (list 
(list 5120.5625 114.6014) 
(list 5194.585 115.0514) 
(list 5194.585 115.2284) 
(list 5120.5625 114.6784)))
(apply 'command (append '("pline") coords '("c")))
(setq currobj (ssadd (entlast) currobj))
(setq coords (list 
(list 5120.5625 114.8214) 
(list 5194.585 115.3714) 
(list 5194.585 115.5484) 
(list 5120.5625 114.8984)))
(apply 'command (append '("pline") coords '("c")))
(setq currobj (ssadd (entlast) currobj))
(setq coords (list 
(list 5120.5625 115.0414) 
(list 5194.585 115.6914) 
(list 5194.585 115.8684) 
(list 5120.5625 115.1184)))
(apply 'command (append '("pline") coords '("c")))
(setq currobj (ssadd (entlast) currobj))
(setq coords (list 
(list 5119.4375 115.1184) 
(list 5045.415 115.8684) 
(list 5045.415 115.6914) 
(list 5119.4375 115.0414)))
(apply 'command (append '("pline") coords '("c")))
(setq currobj (ssadd (entlast) currobj))
(setq coords (list 
(list 5119.4375 114.8984) 
(list 5045.415 115.5484) 
(list 5045.415 115.3714) 
(list 5119.4375 114.8214)))
(apply 'command (append '("pline") coords '("c")))
(setq currobj (ssadd (entlast) currobj))
(setq coords (list 
(list 5119.4375 114.6784) 
(list 5045.415 115.2284) 
(list 5045.415 115.0514) 
(list 5119.4375 114.6014)))
(apply 'command (append '("pline") coords '("c")))
(setq currobj (ssadd (entlast) currobj))
(setq coords (list 
(list 5119.4375 114.4584) 
(list 5045.415 114.9084) 
(list 5045.415 114.7314) 
(list 5119.4375 114.3814)))
(apply 'command (append '("pline") coords '("c")))
(setq currobj (ssadd (entlast) currobj))
(setq coords (list 
(list 5119.4375 114.2384) 
(list 5045.415 114.5884) 
(list 5045.415 114.4114) 
(list 5119.4375 114.1614)))
(apply 'command (append '("pline") coords '("c")))
(setq currobj (ssadd (entlast) currobj))
(setq coords (list 
(list 5119.4375 114.0184) 
(list 5045.415 114.2684) 
(list 5045.415 114.0914) 
(list 5119.4375 113.9414)))
(apply 'command (append '("pline") coords '("c")))
(setq currobj (ssadd (entlast) currobj))
(setq coords (list 
(list 5119.4375 113.7984) 
(list 5045.415 113.9484) 
(list 5045.415 113.7714) 
(list 5119.4375 113.7214)))
(apply 'command (append '("pline") coords '("c")))
(setq currobj (ssadd (entlast) currobj))
(setq coords (list 
(list 5119.4375 113.5784) 
(list 5045.415 113.6284) 
(list 5045.415 113.4514) 
(list 5119.4375 113.5014)))
(apply 'command (append '("pline") coords '("c")))
(setq currobj (ssadd (entlast) currobj))
(setq coords (list 
(list 5119.4375 113.3584) 
(list 5045.415 113.3084) 
(list 5045.415 113.1314) 
(list 5119.4375 113.2814)))
(apply 'command (append '("pline") coords '("c")))
(setq currobj (ssadd (entlast) currobj))
(setq coords (list 
(list 5119.4375 113.1384) 
(list 5045.415 112.9884) 
(list 5045.415 112.8114) 
(list 5119.4375 113.0614)))
(apply 'command (append '("pline") coords '("c")))
(setq currobj (ssadd (entlast) currobj))
(setq coords (list 
(list 5119.4375 112.9184) 
(list 5045.415 112.6684) 
(list 5045.415 112.4914) 
(list 5119.4375 112.8414)))
(apply 'command (append '("pline") coords '("c")))
(setq currobj (ssadd (entlast) currobj))
(setq coords (list 
(list 5119.4375 112.6984) 
(list 5045.415 112.3484) 
(list 5045.415 112.1714) 
(list 5119.4375 112.6214)))
(apply 'command (append '("pline") coords '("c")))
(setq currobj (ssadd (entlast) currobj))
(setq coords (list 
(list 5119.4375 112.4784) 
(list 5045.415 112.0284) 
(list 5045.415 111.8514) 
(list 5119.4375 112.4014)))
(apply 'command (append '("pline") coords '("c")))
(setq currobj (ssadd (entlast) currobj))
(setq coords (list 
(list 5119.4375 112.2584) 
(list 5045.415 111.7084) 
(list 5045.415 111.5314) 
(list 5119.4375 112.1814)))
(apply 'command (append '("pline") coords '("c")))
(setq currobj (ssadd (entlast) currobj))
(setq coords (list 
(list 5119.4375 112.0384) 
(list 5045.415 111.3884) 
(list 5045.415 111.2114) 
(list 5119.4375 111.9614)))
(apply 'command (append '("pline") coords '("c")))
(setq currobj (ssadd (entlast) currobj))
(command "_layer" "set" "nitride" "")
(command "_layer" "set" "text" "")
(command "_circle" "5119.0625,100.8184" "0.075")
(command "_circle" "5119.0625,101.1184" "0.075")
(command "_circle" "5119.0625,101.4184" "0.075")
(command "_circle" "5119.0625,101.7184" "0.075")
(command "_circle" "5119.0625,102.0184" "0.075")
(command "_circle" "5118.7625,100.8184" "0.075")
(command "_circle" "5118.7625,101.1184" "0.075")
(command "_circle" "5118.7625,101.4184" "0.075")
(command "_circle" "5118.7625,101.7184" "0.075")
(command "_circle" "5118.7625,102.0184" "0.075")
(command "_circle" "5118.4625,100.8184" "0.075")
(command "_circle" "5118.4625,101.1184" "0.075")
(command "_circle" "5118.4625,101.4184" "0.075")
(command "_circle" "5118.4625,101.7184" "0.075")
(command "_circle" "5118.4625,102.0184" "0.075")
(command "_circle" "5118.1625,100.8184" "0.075")
(command "_circle" "5118.1625,101.1184" "0.075")
(command "_circle" "5118.1625,101.4184" "0.075")
(command "_circle" "5118.1625,101.7184" "0.075")
(command "_circle" "5118.1625,102.0184" "0.075")
(command "_circle" "5117.8625,100.8184" "0.075")
(command "_circle" "5117.8625,101.1184" "0.075")
(command "_circle" "5117.8625,101.4184" "0.075")
(command "_circle" "5117.8625,101.7184" "0.075")
(command "_circle" "5117.8625,102.0184" "0.075")
(command "_layer" "set" "nitride" "")
(setq coords (list 
(list 5120.2625 126.2614) 
(list 5120.2625 241.9061) 
(list 5119.7375 241.9061) 
(list 5119.7375 126.2614)))
(apply 'command (append '("pline") coords '("c")))
(setq currobj (ssadd (entlast) currobj))
(command "_layer" "set" "prebias" "")
(command "_rectangle" "5119.7375,126.2614" "5120.2625,241.9061")
(setq currobj (ssadd (entlast) currobj))
(command "_layer" "set" "nitride" "")
(setq coords (list 
(list 5120.2625 241.9061) 
(list 5120.5625 251.9061) 
(list 5120.5625 251.9061) 
(list 5120.5625 252.9061) 
(list 5194.585 252.1561) 
(list 5194.585 257.0991) 
(list 5120.5625 256.3491) 
(list 5120.5625 257.3491) 
(list 5120.5625 257.3491) 
(list 5120.2625 267.3491) 
(list 5119.7375 267.3491) 
(list 5119.4375 257.3491) 
(list 5119.4375 257.3491) 
(list 5119.4375 256.3491) 
(list 5045.415 257.0991) 
(list 5045.415 252.1561) 
(list 5119.4375 252.9061) 
(list 5119.4375 251.9061) 
(list 5119.4375 251.9061) 
(list 5119.7375 241.9061)))
(apply 'command (append '("pline") coords '("c")))
(setq currobj (ssadd (entlast) currobj))
(command "_layer" "set" "prebias" "")
(setq coords (list 
(list 5119.4375 241.9061) 
(list 5119.4375 252.9061) 
(list 5045.415 252.1561) 
(list 5045.415 257.0991) 
(list 5119.4375 256.3491) 
(list 5119.4375 267.3491) 
(list 5120.5625 267.3491) 
(list 5120.5625 256.3491) 
(list 5194.585 257.0991) 
(list 5194.585 252.1561) 
(list 5120.5625 252.9061) 
(list 5120.5625 241.9061)))
(apply 'command (append '("pline") coords '("c")))
(setq currobj (ssadd (entlast) currobj))
(command "_layer" "set" "nitride" "")
(command "_layer" "set" "fda1" "")
(setq coords (list 
(list 5120.5625 253.0491) 
(list 5194.585 252.2991) 
(list 5194.585 252.4761) 
(list 5120.5625 253.1261)))
(apply 'command (append '("pline") coords '("c")))
(setq currobj (ssadd (entlast) currobj))
(setq coords (list 
(list 5120.5625 253.2691) 
(list 5194.585 252.6191) 
(list 5194.585 252.7961) 
(list 5120.5625 253.3461)))
(apply 'command (append '("pline") coords '("c")))
(setq currobj (ssadd (entlast) currobj))
(setq coords (list 
(list 5120.5625 253.4891) 
(list 5194.585 252.9391) 
(list 5194.585 253.1161) 
(list 5120.5625 253.5661)))
(apply 'command (append '("pline") coords '("c")))
(setq currobj (ssadd (entlast) currobj))
(setq coords (list 
(list 5120.5625 253.7091) 
(list 5194.585 253.2591) 
(list 5194.585 253.4361) 
(list 5120.5625 253.7861)))
(apply 'command (append '("pline") coords '("c")))
(setq currobj (ssadd (entlast) currobj))
(setq coords (list 
(list 5120.5625 253.9291) 
(list 5194.585 253.5791) 
(list 5194.585 253.7561) 
(list 5120.5625 254.0061)))
(apply 'command (append '("pline") coords '("c")))
(setq currobj (ssadd (entlast) currobj))
(setq coords (list 
(list 5120.5625 254.1491) 
(list 5194.585 253.8991) 
(list 5194.585 254.0761) 
(list 5120.5625 254.2261)))
(apply 'command (append '("pline") coords '("c")))
(setq currobj (ssadd (entlast) currobj))
(setq coords (list 
(list 5120.5625 254.3691) 
(list 5194.585 254.2191) 
(list 5194.585 254.3961) 
(list 5120.5625 254.4461)))
(apply 'command (append '("pline") coords '("c")))
(setq currobj (ssadd (entlast) currobj))
(setq coords (list 
(list 5120.5625 254.5891) 
(list 5194.585 254.5391) 
(list 5194.585 254.7161) 
(list 5120.5625 254.6661)))
(apply 'command (append '("pline") coords '("c")))
(setq currobj (ssadd (entlast) currobj))
(setq coords (list 
(list 5120.5625 254.8091) 
(list 5194.585 254.8591) 
(list 5194.585 255.0361) 
(list 5120.5625 254.8861)))
(apply 'command (append '("pline") coords '("c")))
(setq currobj (ssadd (entlast) currobj))
(setq coords (list 
(list 5120.5625 255.0291) 
(list 5194.585 255.1791) 
(list 5194.585 255.3561) 
(list 5120.5625 255.1061)))
(apply 'command (append '("pline") coords '("c")))
(setq currobj (ssadd (entlast) currobj))
(setq coords (list 
(list 5120.5625 255.2491) 
(list 5194.585 255.4991) 
(list 5194.585 255.6761) 
(list 5120.5625 255.3261)))
(apply 'command (append '("pline") coords '("c")))
(setq currobj (ssadd (entlast) currobj))
(setq coords (list 
(list 5120.5625 255.4691) 
(list 5194.585 255.8191) 
(list 5194.585 255.9961) 
(list 5120.5625 255.5461)))
(apply 'command (append '("pline") coords '("c")))
(setq currobj (ssadd (entlast) currobj))
(setq coords (list 
(list 5120.5625 255.6891) 
(list 5194.585 256.1391) 
(list 5194.585 256.3161) 
(list 5120.5625 255.7661)))
(apply 'command (append '("pline") coords '("c")))
(setq currobj (ssadd (entlast) currobj))
(setq coords (list 
(list 5120.5625 255.9091) 
(list 5194.585 256.4591) 
(list 5194.585 256.6361) 
(list 5120.5625 255.9861)))
(apply 'command (append '("pline") coords '("c")))
(setq currobj (ssadd (entlast) currobj))
(setq coords (list 
(list 5120.5625 256.1291) 
(list 5194.585 256.7791) 
(list 5194.585 256.9561) 
(list 5120.5625 256.2061)))
(apply 'command (append '("pline") coords '("c")))
(setq currobj (ssadd (entlast) currobj))
(setq coords (list 
(list 5119.4375 256.2061) 
(list 5045.415 256.9561) 
(list 5045.415 256.7791) 
(list 5119.4375 256.1291)))
(apply 'command (append '("pline") coords '("c")))
(setq currobj (ssadd (entlast) currobj))
(setq coords (list 
(list 5119.4375 255.9861) 
(list 5045.415 256.6361) 
(list 5045.415 256.4591) 
(list 5119.4375 255.9091)))
(apply 'command (append '("pline") coords '("c")))
(setq currobj (ssadd (entlast) currobj))
(setq coords (list 
(list 5119.4375 255.7661) 
(list 5045.415 256.3161) 
(list 5045.415 256.1391) 
(list 5119.4375 255.6891)))
(apply 'command (append '("pline") coords '("c")))
(setq currobj (ssadd (entlast) currobj))
(setq coords (list 
(list 5119.4375 255.5461) 
(list 5045.415 255.9961) 
(list 5045.415 255.8191) 
(list 5119.4375 255.4691)))
(apply 'command (append '("pline") coords '("c")))
(setq currobj (ssadd (entlast) currobj))
(setq coords (list 
(list 5119.4375 255.3261) 
(list 5045.415 255.6761) 
(list 5045.415 255.4991) 
(list 5119.4375 255.2491)))
(apply 'command (append '("pline") coords '("c")))
(setq currobj (ssadd (entlast) currobj))
(setq coords (list 
(list 5119.4375 255.1061) 
(list 5045.415 255.3561) 
(list 5045.415 255.1791) 
(list 5119.4375 255.0291)))
(apply 'command (append '("pline") coords '("c")))
(setq currobj (ssadd (entlast) currobj))
(setq coords (list 
(list 5119.4375 254.8861) 
(list 5045.415 255.0361) 
(list 5045.415 254.8591) 
(list 5119.4375 254.8091)))
(apply 'command (append '("pline") coords '("c")))
(setq currobj (ssadd (entlast) currobj))
(setq coords (list 
(list 5119.4375 254.6661) 
(list 5045.415 254.7161) 
(list 5045.415 254.5391) 
(list 5119.4375 254.5891)))
(apply 'command (append '("pline") coords '("c")))
(setq currobj (ssadd (entlast) currobj))
(setq coords (list 
(list 5119.4375 254.4461) 
(list 5045.415 254.3961) 
(list 5045.415 254.2191) 
(list 5119.4375 254.3691)))
(apply 'command (append '("pline") coords '("c")))
(setq currobj (ssadd (entlast) currobj))
(setq coords (list 
(list 5119.4375 254.2261) 
(list 5045.415 254.0761) 
(list 5045.415 253.8991) 
(list 5119.4375 254.1491)))
(apply 'command (append '("pline") coords '("c")))
(setq currobj (ssadd (entlast) currobj))
(setq coords (list 
(list 5119.4375 254.0061) 
(list 5045.415 253.7561) 
(list 5045.415 253.5791) 
(list 5119.4375 253.9291)))
(apply 'command (append '("pline") coords '("c")))
(setq currobj (ssadd (entlast) currobj))
(setq coords (list 
(list 5119.4375 253.7861) 
(list 5045.415 253.4361) 
(list 5045.415 253.2591) 
(list 5119.4375 253.7091)))
(apply 'command (append '("pline") coords '("c")))
(setq currobj (ssadd (entlast) currobj))
(setq coords (list 
(list 5119.4375 253.5661) 
(list 5045.415 253.1161) 
(list 5045.415 252.9391) 
(list 5119.4375 253.4891)))
(apply 'command (append '("pline") coords '("c")))
(setq currobj (ssadd (entlast) currobj))
(setq coords (list 
(list 5119.4375 253.3461) 
(list 5045.415 252.7961) 
(list 5045.415 252.6191) 
(list 5119.4375 253.2691)))
(apply 'command (append '("pline") coords '("c")))
(setq currobj (ssadd (entlast) currobj))
(setq coords (list 
(list 5119.4375 253.1261) 
(list 5045.415 252.4761) 
(list 5045.415 252.2991) 
(list 5119.4375 253.0491)))
(apply 'command (append '("pline") coords '("c")))
(setq currobj (ssadd (entlast) currobj))
(command "_layer" "set" "nitride" "")
(command "_layer" "set" "text" "")
(command "_circle" "5119.0625,241.9061" "0.075")
(command "_circle" "5119.0625,242.2061" "0.075")
(command "_circle" "5119.0625,242.5061" "0.075")
(command "_circle" "5119.0625,242.8061" "0.075")
(command "_circle" "5119.0625,243.1061" "0.075")
(command "_circle" "5118.7625,241.9061" "0.075")
(command "_circle" "5118.7625,242.2061" "0.075")
(command "_circle" "5118.7625,242.5061" "0.075")
(command "_circle" "5118.7625,242.8061" "0.075")
(command "_circle" "5118.7625,243.1061" "0.075")
(command "_circle" "5118.4625,241.9061" "0.075")
(command "_circle" "5118.4625,242.2061" "0.075")
(command "_circle" "5118.4625,242.5061" "0.075")
(command "_circle" "5118.4625,242.8061" "0.075")
(command "_circle" "5118.4625,243.1061" "0.075")
(command "_circle" "5118.1625,241.9061" "0.075")
(command "_circle" "5118.1625,242.2061" "0.075")
(command "_circle" "5118.1625,242.5061" "0.075")
(command "_circle" "5118.1625,242.8061" "0.075")
(command "_circle" "5118.1625,243.1061" "0.075")
(command "_circle" "5117.8625,241.9061" "0.075")
(command "_circle" "5117.8625,242.2061" "0.075")
(command "_circle" "5117.8625,242.5061" "0.075")
(command "_circle" "5117.8625,242.8061" "0.075")
(command "_circle" "5117.8625,243.1061" "0.075")
(command "_layer" "set" "nitride" "")
(setq coords (list 
(list 5120.2625 267.3491) 
(list 5120.2625 382.9939) 
(list 5119.7375 382.9939) 
(list 5119.7375 267.3491)))
(apply 'command (append '("pline") coords '("c")))
(setq currobj (ssadd (entlast) currobj))
(command "_layer" "set" "prebias" "")
(command "_rectangle" "5119.7375,267.3491" "5120.2625,382.9939")
(setq currobj (ssadd (entlast) currobj))
(command "_layer" "set" "nitride" "")
(setq coords (list 
(list 5120.2625 382.9939) 
(list 5120.5625 392.9939) 
(list 5120.5625 392.9939) 
(list 5120.5625 393.9939) 
(list 5194.585 393.2439) 
(list 5194.585 398.1869) 
(list 5120.5625 397.4369) 
(list 5120.5625 398.4369) 
(list 5120.5625 398.4369) 
(list 5120.2625 408.4369) 
(list 5119.7375 408.4369) 
(list 5119.4375 398.4369) 
(list 5119.4375 398.4369) 
(list 5119.4375 397.4369) 
(list 5045.415 398.1869) 
(list 5045.415 393.2439) 
(list 5119.4375 393.9939) 
(list 5119.4375 392.9939) 
(list 5119.4375 392.9939) 
(list 5119.7375 382.9939)))
(apply 'command (append '("pline") coords '("c")))
(setq currobj (ssadd (entlast) currobj))
(command "_layer" "set" "prebias" "")
(setq coords (list 
(list 5119.4375 382.9939) 
(list 5119.4375 393.9939) 
(list 5045.415 393.2439) 
(list 5045.415 398.1869) 
(list 5119.4375 397.4369) 
(list 5119.4375 408.4369) 
(list 5120.5625 408.4369) 
(list 5120.5625 397.4369) 
(list 5194.585 398.1869) 
(list 5194.585 393.2439) 
(list 5120.5625 393.9939) 
(list 5120.5625 382.9939)))
(apply 'command (append '("pline") coords '("c")))
(setq currobj (ssadd (entlast) currobj))
(command "_layer" "set" "nitride" "")
(command "_layer" "set" "fda1" "")
(setq coords (list 
(list 5120.5625 394.1369) 
(list 5194.585 393.3869) 
(list 5194.585 393.5639) 
(list 5120.5625 394.2139)))
(apply 'command (append '("pline") coords '("c")))
(setq currobj (ssadd (entlast) currobj))
(setq coords (list 
(list 5120.5625 394.3569) 
(list 5194.585 393.7069) 
(list 5194.585 393.8839) 
(list 5120.5625 394.4339)))
(apply 'command (append '("pline") coords '("c")))
(setq currobj (ssadd (entlast) currobj))
(setq coords (list 
(list 5120.5625 394.5769) 
(list 5194.585 394.0269) 
(list 5194.585 394.2039) 
(list 5120.5625 394.6539)))
(apply 'command (append '("pline") coords '("c")))
(setq currobj (ssadd (entlast) currobj))
(setq coords (list 
(list 5120.5625 394.7969) 
(list 5194.585 394.3469) 
(list 5194.585 394.5239) 
(list 5120.5625 394.8739)))
(apply 'command (append '("pline") coords '("c")))
(setq currobj (ssadd (entlast) currobj))
(setq coords (list 
(list 5120.5625 395.0169) 
(list 5194.585 394.6669) 
(list 5194.585 394.8439) 
(list 5120.5625 395.0939)))
(apply 'command (append '("pline") coords '("c")))
(setq currobj (ssadd (entlast) currobj))
(setq coords (list 
(list 5120.5625 395.2369) 
(list 5194.585 394.9869) 
(list 5194.585 395.1639) 
(list 5120.5625 395.3139)))
(apply 'command (append '("pline") coords '("c")))
(setq currobj (ssadd (entlast) currobj))
(setq coords (list 
(list 5120.5625 395.4569) 
(list 5194.585 395.3069) 
(list 5194.585 395.4839) 
(list 5120.5625 395.5339)))
(apply 'command (append '("pline") coords '("c")))
(setq currobj (ssadd (entlast) currobj))
(setq coords (list 
(list 5120.5625 395.6769) 
(list 5194.585 395.6269) 
(list 5194.585 395.8039) 
(list 5120.5625 395.7539)))
(apply 'command (append '("pline") coords '("c")))
(setq currobj (ssadd (entlast) currobj))
(setq coords (list 
(list 5120.5625 395.8969) 
(list 5194.585 395.9469) 
(list 5194.585 396.1239) 
(list 5120.5625 395.9739)))
(apply 'command (append '("pline") coords '("c")))
(setq currobj (ssadd (entlast) currobj))
(setq coords (list 
(list 5120.5625 396.1169) 
(list 5194.585 396.2669) 
(list 5194.585 396.4439) 
(list 5120.5625 396.1939)))
(apply 'command (append '("pline") coords '("c")))
(setq currobj (ssadd (entlast) currobj))
(setq coords (list 
(list 5120.5625 396.3369) 
(list 5194.585 396.5869) 
(list 5194.585 396.7639) 
(list 5120.5625 396.4139)))
(apply 'command (append '("pline") coords '("c")))
(setq currobj (ssadd (entlast) currobj))
(setq coords (list 
(list 5120.5625 396.5569) 
(list 5194.585 396.9069) 
(list 5194.585 397.0839) 
(list 5120.5625 396.6339)))
(apply 'command (append '("pline") coords '("c")))
(setq currobj (ssadd (entlast) currobj))
(setq coords (list 
(list 5120.5625 396.7769) 
(list 5194.585 397.2269) 
(list 5194.585 397.4039) 
(list 5120.5625 396.8539)))
(apply 'command (append '("pline") coords '("c")))
(setq currobj (ssadd (entlast) currobj))
(setq coords (list 
(list 5120.5625 396.9969) 
(list 5194.585 397.5469) 
(list 5194.585 397.7239) 
(list 5120.5625 397.0739)))
(apply 'command (append '("pline") coords '("c")))
(setq currobj (ssadd (entlast) currobj))
(setq coords (list 
(list 5120.5625 397.2169) 
(list 5194.585 397.8669) 
(list 5194.585 398.0439) 
(list 5120.5625 397.2939)))
(apply 'command (append '("pline") coords '("c")))
(setq currobj (ssadd (entlast) currobj))
(setq coords (list 
(list 5119.4375 397.2939) 
(list 5045.415 398.0439) 
(list 5045.415 397.8669) 
(list 5119.4375 397.2169)))
(apply 'command (append '("pline") coords '("c")))
(setq currobj (ssadd (entlast) currobj))
(setq coords (list 
(list 5119.4375 397.0739) 
(list 5045.415 397.7239) 
(list 5045.415 397.5469) 
(list 5119.4375 396.9969)))
(apply 'command (append '("pline") coords '("c")))
(setq currobj (ssadd (entlast) currobj))
(setq coords (list 
(list 5119.4375 396.8539) 
(list 5045.415 397.4039) 
(list 5045.415 397.2269) 
(list 5119.4375 396.7769)))
(apply 'command (append '("pline") coords '("c")))
(setq currobj (ssadd (entlast) currobj))
(setq coords (list 
(list 5119.4375 396.6339) 
(list 5045.415 397.0839) 
(list 5045.415 396.9069) 
(list 5119.4375 396.5569)))
(apply 'command (append '("pline") coords '("c")))
(setq currobj (ssadd (entlast) currobj))
(setq coords (list 
(list 5119.4375 396.4139) 
(list 5045.415 396.7639) 
(list 5045.415 396.5869) 
(list 5119.4375 396.3369)))
(apply 'command (append '("pline") coords '("c")))
(setq currobj (ssadd (entlast) currobj))
(setq coords (list 
(list 5119.4375 396.1939) 
(list 5045.415 396.4439) 
(list 5045.415 396.2669) 
(list 5119.4375 396.1169)))
(apply 'command (append '("pline") coords '("c")))
(setq currobj (ssadd (entlast) currobj))
(setq coords (list 
(list 5119.4375 395.9739) 
(list 5045.415 396.1239) 
(list 5045.415 395.9469) 
(list 5119.4375 395.8969)))
(apply 'command (append '("pline") coords '("c")))
(setq currobj (ssadd (entlast) currobj))
(setq coords (list 
(list 5119.4375 395.7539) 
(list 5045.415 395.8039) 
(list 5045.415 395.6269) 
(list 5119.4375 395.6769)))
(apply 'command (append '("pline") coords '("c")))
(setq currobj (ssadd (entlast) currobj))
(setq coords (list 
(list 5119.4375 395.5339) 
(list 5045.415 395.4839) 
(list 5045.415 395.3069) 
(list 5119.4375 395.4569)))
(apply 'command (append '("pline") coords '("c")))
(setq currobj (ssadd (entlast) currobj))
(setq coords (list 
(list 5119.4375 395.3139) 
(list 5045.415 395.1639) 
(list 5045.415 394.9869) 
(list 5119.4375 395.2369)))
(apply 'command (append '("pline") coords '("c")))
(setq currobj (ssadd (entlast) currobj))
(setq coords (list 
(list 5119.4375 395.0939) 
(list 5045.415 394.8439) 
(list 5045.415 394.6669) 
(list 5119.4375 395.0169)))
(apply 'command (append '("pline") coords '("c")))
(setq currobj (ssadd (entlast) currobj))
(setq coords (list 
(list 5119.4375 394.8739) 
(list 5045.415 394.5239) 
(list 5045.415 394.3469) 
(list 5119.4375 394.7969)))
(apply 'command (append '("pline") coords '("c")))
(setq currobj (ssadd (entlast) currobj))
(setq coords (list 
(list 5119.4375 394.6539) 
(list 5045.415 394.2039) 
(list 5045.415 394.0269) 
(list 5119.4375 394.5769)))
(apply 'command (append '("pline") coords '("c")))
(setq currobj (ssadd (entlast) currobj))
(setq coords (list 
(list 5119.4375 394.4339) 
(list 5045.415 393.8839) 
(list 5045.415 393.7069) 
(list 5119.4375 394.3569)))
(apply 'command (append '("pline") coords '("c")))
(setq currobj (ssadd (entlast) currobj))
(setq coords (list 
(list 5119.4375 394.2139) 
(list 5045.415 393.5639) 
(list 5045.415 393.3869) 
(list 5119.4375 394.1369)))
(apply 'command (append '("pline") coords '("c")))
(setq currobj (ssadd (entlast) currobj))
(command "_layer" "set" "nitride" "")
(command "_layer" "set" "text" "")
(command "_circle" "5119.0625,382.9939" "0.075")
(command "_circle" "5119.0625,383.2939" "0.075")
(command "_circle" "5119.0625,383.5939" "0.075")
(command "_circle" "5119.0625,383.8939" "0.075")
(command "_circle" "5119.0625,384.1939" "0.075")
(command "_circle" "5118.7625,382.9939" "0.075")
(command "_circle" "5118.7625,383.2939" "0.075")
(command "_circle" "5118.7625,383.5939" "0.075")
(command "_circle" "5118.7625,383.8939" "0.075")
(command "_circle" "5118.7625,384.1939" "0.075")
(command "_circle" "5118.4625,382.9939" "0.075")
(command "_circle" "5118.4625,383.2939" "0.075")
(command "_circle" "5118.4625,383.5939" "0.075")
(command "_circle" "5118.4625,383.8939" "0.075")
(command "_circle" "5118.4625,384.1939" "0.075")
(command "_circle" "5118.1625,382.9939" "0.075")
(command "_circle" "5118.1625,383.2939" "0.075")
(command "_circle" "5118.1625,383.5939" "0.075")
(command "_circle" "5118.1625,383.8939" "0.075")
(command "_circle" "5118.1625,384.1939" "0.075")
(command "_circle" "5117.8625,382.9939" "0.075")
(command "_circle" "5117.8625,383.2939" "0.075")
(command "_circle" "5117.8625,383.5939" "0.075")
(command "_circle" "5117.8625,383.8939" "0.075")
(command "_circle" "5117.8625,384.1939" "0.075")
(command "_layer" "set" "nitride" "")
(setq coords (list 
(list 5120.2625 408.4369) 
(list 5120.2625 524.0816) 
(list 5119.7375 524.0816) 
(list 5119.7375 408.4369)))
(apply 'command (append '("pline") coords '("c")))
(setq currobj (ssadd (entlast) currobj))
(command "_layer" "set" "prebias" "")
(command "_rectangle" "5119.7375,408.4369" "5120.2625,524.0816")
(setq currobj (ssadd (entlast) currobj))
(command "_layer" "set" "nitride" "")
(setq coords (list 
(list 5120.2625 524.0816) 
(list 5120.5625 534.0816) 
(list 5120.5625 534.0816) 
(list 5120.5625 535.0816) 
(list 5194.585 534.3316) 
(list 5194.585 539.2746) 
(list 5120.5625 538.5246) 
(list 5120.5625 539.5246) 
(list 5120.5625 539.5246) 
(list 5120.2625 549.5246) 
(list 5119.7375 549.5246) 
(list 5119.4375 539.5246) 
(list 5119.4375 539.5246) 
(list 5119.4375 538.5246) 
(list 5045.415 539.2746) 
(list 5045.415 534.3316) 
(list 5119.4375 535.0816) 
(list 5119.4375 534.0816) 
(list 5119.4375 534.0816) 
(list 5119.7375 524.0816)))
(apply 'command (append '("pline") coords '("c")))
(setq currobj (ssadd (entlast) currobj))
(command "_layer" "set" "prebias" "")
(setq coords (list 
(list 5119.4375 524.0816) 
(list 5119.4375 535.0816) 
(list 5045.415 534.3316) 
(list 5045.415 539.2746) 
(list 5119.4375 538.5246) 
(list 5119.4375 549.5246) 
(list 5120.5625 549.5246) 
(list 5120.5625 538.5246) 
(list 5194.585 539.2746) 
(list 5194.585 534.3316) 
(list 5120.5625 535.0816) 
(list 5120.5625 524.0816)))
(apply 'command (append '("pline") coords '("c")))
(setq currobj (ssadd (entlast) currobj))
(command "_layer" "set" "nitride" "")
(command "_layer" "set" "fda1" "")
(setq coords (list 
(list 5120.5625 535.2246) 
(list 5194.585 534.4746) 
(list 5194.585 534.6516) 
(list 5120.5625 535.3016)))
(apply 'command (append '("pline") coords '("c")))
(setq currobj (ssadd (entlast) currobj))
(setq coords (list 
(list 5120.5625 535.4446) 
(list 5194.585 534.7946) 
(list 5194.585 534.9716) 
(list 5120.5625 535.5216)))
(apply 'command (append '("pline") coords '("c")))
(setq currobj (ssadd (entlast) currobj))
(setq coords (list 
(list 5120.5625 535.6646) 
(list 5194.585 535.1146) 
(list 5194.585 535.2916) 
(list 5120.5625 535.7416)))
(apply 'command (append '("pline") coords '("c")))
(setq currobj (ssadd (entlast) currobj))
(setq coords (list 
(list 5120.5625 535.8846) 
(list 5194.585 535.4346) 
(list 5194.585 535.6116) 
(list 5120.5625 535.9616)))
(apply 'command (append '("pline") coords '("c")))
(setq currobj (ssadd (entlast) currobj))
(setq coords (list 
(list 5120.5625 536.1046) 
(list 5194.585 535.7546) 
(list 5194.585 535.9316) 
(list 5120.5625 536.1816)))
(apply 'command (append '("pline") coords '("c")))
(setq currobj (ssadd (entlast) currobj))
(setq coords (list 
(list 5120.5625 536.3246) 
(list 5194.585 536.0746) 
(list 5194.585 536.2516) 
(list 5120.5625 536.4016)))
(apply 'command (append '("pline") coords '("c")))
(setq currobj (ssadd (entlast) currobj))
(setq coords (list 
(list 5120.5625 536.5446) 
(list 5194.585 536.3946) 
(list 5194.585 536.5716) 
(list 5120.5625 536.6216)))
(apply 'command (append '("pline") coords '("c")))
(setq currobj (ssadd (entlast) currobj))
(setq coords (list 
(list 5120.5625 536.7646) 
(list 5194.585 536.7146) 
(list 5194.585 536.8916) 
(list 5120.5625 536.8416)))
(apply 'command (append '("pline") coords '("c")))
(setq currobj (ssadd (entlast) currobj))
(setq coords (list 
(list 5120.5625 536.9846) 
(list 5194.585 537.0346) 
(list 5194.585 537.2116) 
(list 5120.5625 537.0616)))
(apply 'command (append '("pline") coords '("c")))
(setq currobj (ssadd (entlast) currobj))
(setq coords (list 
(list 5120.5625 537.2046) 
(list 5194.585 537.3546) 
(list 5194.585 537.5316) 
(list 5120.5625 537.2816)))
(apply 'command (append '("pline") coords '("c")))
(setq currobj (ssadd (entlast) currobj))
(setq coords (list 
(list 5120.5625 537.4246) 
(list 5194.585 537.6746) 
(list 5194.585 537.8516) 
(list 5120.5625 537.5016)))
(apply 'command (append '("pline") coords '("c")))
(setq currobj (ssadd (entlast) currobj))
(setq coords (list 
(list 5120.5625 537.6446) 
(list 5194.585 537.9946) 
(list 5194.585 538.1716) 
(list 5120.5625 537.7216)))
(apply 'command (append '("pline") coords '("c")))
(setq currobj (ssadd (entlast) currobj))
(setq coords (list 
(list 5120.5625 537.8646) 
(list 5194.585 538.3146) 
(list 5194.585 538.4916) 
(list 5120.5625 537.9416)))
(apply 'command (append '("pline") coords '("c")))
(setq currobj (ssadd (entlast) currobj))
(setq coords (list 
(list 5120.5625 538.0846) 
(list 5194.585 538.6346) 
(list 5194.585 538.8116) 
(list 5120.5625 538.1616)))
(apply 'command (append '("pline") coords '("c")))
(setq currobj (ssadd (entlast) currobj))
(setq coords (list 
(list 5120.5625 538.3046) 
(list 5194.585 538.9546) 
(list 5194.585 539.1316) 
(list 5120.5625 538.3816)))
(apply 'command (append '("pline") coords '("c")))
(setq currobj (ssadd (entlast) currobj))
(setq coords (list 
(list 5119.4375 538.3816) 
(list 5045.415 539.1316) 
(list 5045.415 538.9546) 
(list 5119.4375 538.3046)))
(apply 'command (append '("pline") coords '("c")))
(setq currobj (ssadd (entlast) currobj))
(setq coords (list 
(list 5119.4375 538.1616) 
(list 5045.415 538.8116) 
(list 5045.415 538.6346) 
(list 5119.4375 538.0846)))
(apply 'command (append '("pline") coords '("c")))
(setq currobj (ssadd (entlast) currobj))
(setq coords (list 
(list 5119.4375 537.9416) 
(list 5045.415 538.4916) 
(list 5045.415 538.3146) 
(list 5119.4375 537.8646)))
(apply 'command (append '("pline") coords '("c")))
(setq currobj (ssadd (entlast) currobj))
(setq coords (list 
(list 5119.4375 537.7216) 
(list 5045.415 538.1716) 
(list 5045.415 537.9946) 
(list 5119.4375 537.6446)))
(apply 'command (append '("pline") coords '("c")))
(setq currobj (ssadd (entlast) currobj))
(setq coords (list 
(list 5119.4375 537.5016) 
(list 5045.415 537.8516) 
(list 5045.415 537.6746) 
(list 5119.4375 537.4246)))
(apply 'command (append '("pline") coords '("c")))
(setq currobj (ssadd (entlast) currobj))
(setq coords (list 
(list 5119.4375 537.2816) 
(list 5045.415 537.5316) 
(list 5045.415 537.3546) 
(list 5119.4375 537.2046)))
(apply 'command (append '("pline") coords '("c")))
(setq currobj (ssadd (entlast) currobj))
(setq coords (list 
(list 5119.4375 537.0616) 
(list 5045.415 537.2116) 
(list 5045.415 537.0346) 
(list 5119.4375 536.9846)))
(apply 'command (append '("pline") coords '("c")))
(setq currobj (ssadd (entlast) currobj))
(setq coords (list 
(list 5119.4375 536.8416) 
(list 5045.415 536.8916) 
(list 5045.415 536.7146) 
(list 5119.4375 536.7646)))
(apply 'command (append '("pline") coords '("c")))
(setq currobj (ssadd (entlast) currobj))
(setq coords (list 
(list 5119.4375 536.6216) 
(list 5045.415 536.5716) 
(list 5045.415 536.3946) 
(list 5119.4375 536.5446)))
(apply 'command (append '("pline") coords '("c")))
(setq currobj (ssadd (entlast) currobj))
(setq coords (list 
(list 5119.4375 536.4016) 
(list 5045.415 536.2516) 
(list 5045.415 536.0746) 
(list 5119.4375 536.3246)))
(apply 'command (append '("pline") coords '("c")))
(setq currobj (ssadd (entlast) currobj))
(setq coords (list 
(list 5119.4375 536.1816) 
(list 5045.415 535.9316) 
(list 5045.415 535.7546) 
(list 5119.4375 536.1046)))
(apply 'command (append '("pline") coords '("c")))
(setq currobj (ssadd (entlast) currobj))
(setq coords (list 
(list 5119.4375 535.9616) 
(list 5045.415 535.6116) 
(list 5045.415 535.4346) 
(list 5119.4375 535.8846)))
(apply 'command (append '("pline") coords '("c")))
(setq currobj (ssadd (entlast) currobj))
(setq coords (list 
(list 5119.4375 535.7416) 
(list 5045.415 535.2916) 
(list 5045.415 535.1146) 
(list 5119.4375 535.6646)))
(apply 'command (append '("pline") coords '("c")))
(setq currobj (ssadd (entlast) currobj))
(setq coords (list 
(list 5119.4375 535.5216) 
(list 5045.415 534.9716) 
(list 5045.415 534.7946) 
(list 5119.4375 535.4446)))
(apply 'command (append '("pline") coords '("c")))
(setq currobj (ssadd (entlast) currobj))
(setq coords (list 
(list 5119.4375 535.3016) 
(list 5045.415 534.6516) 
(list 5045.415 534.4746) 
(list 5119.4375 535.2246)))
(apply 'command (append '("pline") coords '("c")))
(setq currobj (ssadd (entlast) currobj))
(command "_layer" "set" "nitride" "")
(command "_layer" "set" "text" "")
(command "_circle" "5119.0625,524.0816" "0.075")
(command "_circle" "5119.0625,524.3816" "0.075")
(command "_circle" "5119.0625,524.6816" "0.075")
(command "_circle" "5119.0625,524.9816" "0.075")
(command "_circle" "5119.0625,525.2816" "0.075")
(command "_circle" "5118.7625,524.0816" "0.075")
(command "_circle" "5118.7625,524.3816" "0.075")
(command "_circle" "5118.7625,524.6816" "0.075")
(command "_circle" "5118.7625,524.9816" "0.075")
(command "_circle" "5118.7625,525.2816" "0.075")
(command "_circle" "5118.4625,524.0816" "0.075")
(command "_circle" "5118.4625,524.3816" "0.075")
(command "_circle" "5118.4625,524.6816" "0.075")
(command "_circle" "5118.4625,524.9816" "0.075")
(command "_circle" "5118.4625,525.2816" "0.075")
(command "_circle" "5118.1625,524.0816" "0.075")
(command "_circle" "5118.1625,524.3816" "0.075")
(command "_circle" "5118.1625,524.6816" "0.075")
(command "_circle" "5118.1625,524.9816" "0.075")
(command "_circle" "5118.1625,525.2816" "0.075")
(command "_circle" "5117.8625,524.0816" "0.075")
(command "_circle" "5117.8625,524.3816" "0.075")
(command "_circle" "5117.8625,524.6816" "0.075")
(command "_circle" "5117.8625,524.9816" "0.075")
(command "_circle" "5117.8625,525.2816" "0.075")
(command "_layer" "set" "nitride" "")
(setq coords (list 
(list 5120.2625 549.5246) 
(list 5120.2625 665.1693) 
(list 5119.7375 665.1693) 
(list 5119.7375 549.5246)))
(apply 'command (append '("pline") coords '("c")))
(setq currobj (ssadd (entlast) currobj))
(command "_layer" "set" "prebias" "")
(command "_rectangle" "5119.7375,549.5246" "5120.2625,665.1693")
(setq currobj (ssadd (entlast) currobj))
(command "_layer" "set" "nitride" "")
(setq coords (list 
(list 5120.2625 665.1693) 
(list 5120.5625 675.1693) 
(list 5120.5625 675.1693) 
(list 5120.5625 676.1693) 
(list 5194.585 675.4193) 
(list 5194.585 680.3623) 
(list 5120.5625 679.6123) 
(list 5120.5625 680.6123) 
(list 5120.5625 680.6123) 
(list 5120.2625 690.6123) 
(list 5119.7375 690.6123) 
(list 5119.4375 680.6123) 
(list 5119.4375 680.6123) 
(list 5119.4375 679.6123) 
(list 5045.415 680.3623) 
(list 5045.415 675.4193) 
(list 5119.4375 676.1693) 
(list 5119.4375 675.1693) 
(list 5119.4375 675.1693) 
(list 5119.7375 665.1693)))
(apply 'command (append '("pline") coords '("c")))
(setq currobj (ssadd (entlast) currobj))
(command "_layer" "set" "prebias" "")
(setq coords (list 
(list 5119.4375 665.1693) 
(list 5119.4375 676.1693) 
(list 5045.415 675.4193) 
(list 5045.415 680.3623) 
(list 5119.4375 679.6123) 
(list 5119.4375 690.6123) 
(list 5120.5625 690.6123) 
(list 5120.5625 679.6123) 
(list 5194.585 680.3623) 
(list 5194.585 675.4193) 
(list 5120.5625 676.1693) 
(list 5120.5625 665.1693)))
(apply 'command (append '("pline") coords '("c")))
(setq currobj (ssadd (entlast) currobj))
(command "_layer" "set" "nitride" "")
(command "_layer" "set" "fda1" "")
(setq coords (list 
(list 5120.5625 676.3123) 
(list 5194.585 675.5623) 
(list 5194.585 675.7393) 
(list 5120.5625 676.3893)))
(apply 'command (append '("pline") coords '("c")))
(setq currobj (ssadd (entlast) currobj))
(setq coords (list 
(list 5120.5625 676.5323) 
(list 5194.585 675.8823) 
(list 5194.585 676.0593) 
(list 5120.5625 676.6093)))
(apply 'command (append '("pline") coords '("c")))
(setq currobj (ssadd (entlast) currobj))
(setq coords (list 
(list 5120.5625 676.7523) 
(list 5194.585 676.2023) 
(list 5194.585 676.3793) 
(list 5120.5625 676.8293)))
(apply 'command (append '("pline") coords '("c")))
(setq currobj (ssadd (entlast) currobj))
(setq coords (list 
(list 5120.5625 676.9723) 
(list 5194.585 676.5223) 
(list 5194.585 676.6993) 
(list 5120.5625 677.0493)))
(apply 'command (append '("pline") coords '("c")))
(setq currobj (ssadd (entlast) currobj))
(setq coords (list 
(list 5120.5625 677.1923) 
(list 5194.585 676.8423) 
(list 5194.585 677.0193) 
(list 5120.5625 677.2693)))
(apply 'command (append '("pline") coords '("c")))
(setq currobj (ssadd (entlast) currobj))
(setq coords (list 
(list 5120.5625 677.4123) 
(list 5194.585 677.1623) 
(list 5194.585 677.3393) 
(list 5120.5625 677.4893)))
(apply 'command (append '("pline") coords '("c")))
(setq currobj (ssadd (entlast) currobj))
(setq coords (list 
(list 5120.5625 677.6323) 
(list 5194.585 677.4823) 
(list 5194.585 677.6593) 
(list 5120.5625 677.7093)))
(apply 'command (append '("pline") coords '("c")))
(setq currobj (ssadd (entlast) currobj))
(setq coords (list 
(list 5120.5625 677.8523) 
(list 5194.585 677.8023) 
(list 5194.585 677.9793) 
(list 5120.5625 677.9293)))
(apply 'command (append '("pline") coords '("c")))
(setq currobj (ssadd (entlast) currobj))
(setq coords (list 
(list 5120.5625 678.0723) 
(list 5194.585 678.1223) 
(list 5194.585 678.2993) 
(list 5120.5625 678.1493)))
(apply 'command (append '("pline") coords '("c")))
(setq currobj (ssadd (entlast) currobj))
(setq coords (list 
(list 5120.5625 678.2923) 
(list 5194.585 678.4423) 
(list 5194.585 678.6193) 
(list 5120.5625 678.3693)))
(apply 'command (append '("pline") coords '("c")))
(setq currobj (ssadd (entlast) currobj))
(setq coords (list 
(list 5120.5625 678.5123) 
(list 5194.585 678.7623) 
(list 5194.585 678.9393) 
(list 5120.5625 678.5893)))
(apply 'command (append '("pline") coords '("c")))
(setq currobj (ssadd (entlast) currobj))
(setq coords (list 
(list 5120.5625 678.7323) 
(list 5194.585 679.0823) 
(list 5194.585 679.2593) 
(list 5120.5625 678.8093)))
(apply 'command (append '("pline") coords '("c")))
(setq currobj (ssadd (entlast) currobj))
(setq coords (list 
(list 5120.5625 678.9523) 
(list 5194.585 679.4023) 
(list 5194.585 679.5793) 
(list 5120.5625 679.0293)))
(apply 'command (append '("pline") coords '("c")))
(setq currobj (ssadd (entlast) currobj))
(setq coords (list 
(list 5120.5625 679.1723) 
(list 5194.585 679.7223) 
(list 5194.585 679.8993) 
(list 5120.5625 679.2493)))
(apply 'command (append '("pline") coords '("c")))
(setq currobj (ssadd (entlast) currobj))
(setq coords (list 
(list 5120.5625 679.3923) 
(list 5194.585 680.0423) 
(list 5194.585 680.2193) 
(list 5120.5625 679.4693)))
(apply 'command (append '("pline") coords '("c")))
(setq currobj (ssadd (entlast) currobj))
(setq coords (list 
(list 5119.4375 679.4693) 
(list 5045.415 680.2193) 
(list 5045.415 680.0423) 
(list 5119.4375 679.3923)))
(apply 'command (append '("pline") coords '("c")))
(setq currobj (ssadd (entlast) currobj))
(setq coords (list 
(list 5119.4375 679.2493) 
(list 5045.415 679.8993) 
(list 5045.415 679.7223) 
(list 5119.4375 679.1723)))
(apply 'command (append '("pline") coords '("c")))
(setq currobj (ssadd (entlast) currobj))
(setq coords (list 
(list 5119.4375 679.0293) 
(list 5045.415 679.5793) 
(list 5045.415 679.4023) 
(list 5119.4375 678.9523)))
(apply 'command (append '("pline") coords '("c")))
(setq currobj (ssadd (entlast) currobj))
(setq coords (list 
(list 5119.4375 678.8093) 
(list 5045.415 679.2593) 
(list 5045.415 679.0823) 
(list 5119.4375 678.7323)))
(apply 'command (append '("pline") coords '("c")))
(setq currobj (ssadd (entlast) currobj))
(setq coords (list 
(list 5119.4375 678.5893) 
(list 5045.415 678.9393) 
(list 5045.415 678.7623) 
(list 5119.4375 678.5123)))
(apply 'command (append '("pline") coords '("c")))
(setq currobj (ssadd (entlast) currobj))
(setq coords (list 
(list 5119.4375 678.3693) 
(list 5045.415 678.6193) 
(list 5045.415 678.4423) 
(list 5119.4375 678.2923)))
(apply 'command (append '("pline") coords '("c")))
(setq currobj (ssadd (entlast) currobj))
(setq coords (list 
(list 5119.4375 678.1493) 
(list 5045.415 678.2993) 
(list 5045.415 678.1223) 
(list 5119.4375 678.0723)))
(apply 'command (append '("pline") coords '("c")))
(setq currobj (ssadd (entlast) currobj))
(setq coords (list 
(list 5119.4375 677.9293) 
(list 5045.415 677.9793) 
(list 5045.415 677.8023) 
(list 5119.4375 677.8523)))
(apply 'command (append '("pline") coords '("c")))
(setq currobj (ssadd (entlast) currobj))
(setq coords (list 
(list 5119.4375 677.7093) 
(list 5045.415 677.6593) 
(list 5045.415 677.4823) 
(list 5119.4375 677.6323)))
(apply 'command (append '("pline") coords '("c")))
(setq currobj (ssadd (entlast) currobj))
(setq coords (list 
(list 5119.4375 677.4893) 
(list 5045.415 677.3393) 
(list 5045.415 677.1623) 
(list 5119.4375 677.4123)))
(apply 'command (append '("pline") coords '("c")))
(setq currobj (ssadd (entlast) currobj))
(setq coords (list 
(list 5119.4375 677.2693) 
(list 5045.415 677.0193) 
(list 5045.415 676.8423) 
(list 5119.4375 677.1923)))
(apply 'command (append '("pline") coords '("c")))
(setq currobj (ssadd (entlast) currobj))
(setq coords (list 
(list 5119.4375 677.0493) 
(list 5045.415 676.6993) 
(list 5045.415 676.5223) 
(list 5119.4375 676.9723)))
(apply 'command (append '("pline") coords '("c")))
(setq currobj (ssadd (entlast) currobj))
(setq coords (list 
(list 5119.4375 676.8293) 
(list 5045.415 676.3793) 
(list 5045.415 676.2023) 
(list 5119.4375 676.7523)))
(apply 'command (append '("pline") coords '("c")))
(setq currobj (ssadd (entlast) currobj))
(setq coords (list 
(list 5119.4375 676.6093) 
(list 5045.415 676.0593) 
(list 5045.415 675.8823) 
(list 5119.4375 676.5323)))
(apply 'command (append '("pline") coords '("c")))
(setq currobj (ssadd (entlast) currobj))
(setq coords (list 
(list 5119.4375 676.3893) 
(list 5045.415 675.7393) 
(list 5045.415 675.5623) 
(list 5119.4375 676.3123)))
(apply 'command (append '("pline") coords '("c")))
(setq currobj (ssadd (entlast) currobj))
(command "_layer" "set" "nitride" "")
(command "_layer" "set" "text" "")
(command "_circle" "5119.0625,665.1693" "0.075")
(command "_circle" "5119.0625,665.4693" "0.075")
(command "_circle" "5119.0625,665.7693" "0.075")
(command "_circle" "5119.0625,666.0693" "0.075")
(command "_circle" "5119.0625,666.3693" "0.075")
(command "_circle" "5118.7625,665.1693" "0.075")
(command "_circle" "5118.7625,665.4693" "0.075")
(command "_circle" "5118.7625,665.7693" "0.075")
(command "_circle" "5118.7625,666.0693" "0.075")
(command "_circle" "5118.7625,666.3693" "0.075")
(command "_circle" "5118.4625,665.1693" "0.075")
(command "_circle" "5118.4625,665.4693" "0.075")
(command "_circle" "5118.4625,665.7693" "0.075")
(command "_circle" "5118.4625,666.0693" "0.075")
(command "_circle" "5118.4625,666.3693" "0.075")
(command "_circle" "5118.1625,665.1693" "0.075")
(command "_circle" "5118.1625,665.4693" "0.075")
(command "_circle" "5118.1625,665.7693" "0.075")
(command "_circle" "5118.1625,666.0693" "0.075")
(command "_circle" "5118.1625,666.3693" "0.075")
(command "_circle" "5117.8625,665.1693" "0.075")
(command "_circle" "5117.8625,665.4693" "0.075")
(command "_circle" "5117.8625,665.7693" "0.075")
(command "_circle" "5117.8625,666.0693" "0.075")
(command "_circle" "5117.8625,666.3693" "0.075")
(command "_layer" "set" "nitride" "")
(setq coords (list 
(list 5120.2625 690.6123) 
(list 5120.2625 806.257) 
(list 5119.7375 806.257) 
(list 5119.7375 690.6123)))
(apply 'command (append '("pline") coords '("c")))
(setq currobj (ssadd (entlast) currobj))
(command "_layer" "set" "prebias" "")
(command "_rectangle" "5119.7375,690.6123" "5120.2625,806.257")
(setq currobj (ssadd (entlast) currobj))
(command "_layer" "set" "nitride" "")
(setq coords (list 
(list 5120.2625 806.257) 
(list 5120.5625 816.257) 
(list 5120.5625 816.257) 
(list 5120.5625 817.257) 
(list 5194.585 816.507) 
(list 5194.585 821.45) 
(list 5120.5625 820.7) 
(list 5120.5625 821.7) 
(list 5120.5625 821.7) 
(list 5120.2625 831.7) 
(list 5119.7375 831.7) 
(list 5119.4375 821.7) 
(list 5119.4375 821.7) 
(list 5119.4375 820.7) 
(list 5045.415 821.45) 
(list 5045.415 816.507) 
(list 5119.4375 817.257) 
(list 5119.4375 816.257) 
(list 5119.4375 816.257) 
(list 5119.7375 806.257)))
(apply 'command (append '("pline") coords '("c")))
(setq currobj (ssadd (entlast) currobj))
(command "_layer" "set" "prebias" "")
(setq coords (list 
(list 5119.4375 806.257) 
(list 5119.4375 817.257) 
(list 5045.415 816.507) 
(list 5045.415 821.45) 
(list 5119.4375 820.7) 
(list 5119.4375 831.7) 
(list 5120.5625 831.7) 
(list 5120.5625 820.7) 
(list 5194.585 821.45) 
(list 5194.585 816.507) 
(list 5120.5625 817.257) 
(list 5120.5625 806.257)))
(apply 'command (append '("pline") coords '("c")))
(setq currobj (ssadd (entlast) currobj))
(command "_layer" "set" "nitride" "")
(command "_layer" "set" "fda1" "")
(setq coords (list 
(list 5120.5625 817.4) 
(list 5194.585 816.65) 
(list 5194.585 816.827) 
(list 5120.5625 817.477)))
(apply 'command (append '("pline") coords '("c")))
(setq currobj (ssadd (entlast) currobj))
(setq coords (list 
(list 5120.5625 817.62) 
(list 5194.585 816.97) 
(list 5194.585 817.147) 
(list 5120.5625 817.697)))
(apply 'command (append '("pline") coords '("c")))
(setq currobj (ssadd (entlast) currobj))
(setq coords (list 
(list 5120.5625 817.84) 
(list 5194.585 817.29) 
(list 5194.585 817.467) 
(list 5120.5625 817.917)))
(apply 'command (append '("pline") coords '("c")))
(setq currobj (ssadd (entlast) currobj))
(setq coords (list 
(list 5120.5625 818.06) 
(list 5194.585 817.61) 
(list 5194.585 817.787) 
(list 5120.5625 818.137)))
(apply 'command (append '("pline") coords '("c")))
(setq currobj (ssadd (entlast) currobj))
(setq coords (list 
(list 5120.5625 818.28) 
(list 5194.585 817.93) 
(list 5194.585 818.107) 
(list 5120.5625 818.357)))
(apply 'command (append '("pline") coords '("c")))
(setq currobj (ssadd (entlast) currobj))
(setq coords (list 
(list 5120.5625 818.5) 
(list 5194.585 818.25) 
(list 5194.585 818.427) 
(list 5120.5625 818.577)))
(apply 'command (append '("pline") coords '("c")))
(setq currobj (ssadd (entlast) currobj))
(setq coords (list 
(list 5120.5625 818.72) 
(list 5194.585 818.57) 
(list 5194.585 818.747) 
(list 5120.5625 818.797)))
(apply 'command (append '("pline") coords '("c")))
(setq currobj (ssadd (entlast) currobj))
(setq coords (list 
(list 5120.5625 818.94) 
(list 5194.585 818.89) 
(list 5194.585 819.067) 
(list 5120.5625 819.017)))
(apply 'command (append '("pline") coords '("c")))
(setq currobj (ssadd (entlast) currobj))
(setq coords (list 
(list 5120.5625 819.16) 
(list 5194.585 819.21) 
(list 5194.585 819.387) 
(list 5120.5625 819.237)))
(apply 'command (append '("pline") coords '("c")))
(setq currobj (ssadd (entlast) currobj))
(setq coords (list 
(list 5120.5625 819.38) 
(list 5194.585 819.53) 
(list 5194.585 819.707) 
(list 5120.5625 819.457)))
(apply 'command (append '("pline") coords '("c")))
(setq currobj (ssadd (entlast) currobj))
(setq coords (list 
(list 5120.5625 819.6) 
(list 5194.585 819.85) 
(list 5194.585 820.027) 
(list 5120.5625 819.677)))
(apply 'command (append '("pline") coords '("c")))
(setq currobj (ssadd (entlast) currobj))
(setq coords (list 
(list 5120.5625 819.82) 
(list 5194.585 820.17) 
(list 5194.585 820.347) 
(list 5120.5625 819.897)))
(apply 'command (append '("pline") coords '("c")))
(setq currobj (ssadd (entlast) currobj))
(setq coords (list 
(list 5120.5625 820.04) 
(list 5194.585 820.49) 
(list 5194.585 820.667) 
(list 5120.5625 820.117)))
(apply 'command (append '("pline") coords '("c")))
(setq currobj (ssadd (entlast) currobj))
(setq coords (list 
(list 5120.5625 820.26) 
(list 5194.585 820.81) 
(list 5194.585 820.987) 
(list 5120.5625 820.337)))
(apply 'command (append '("pline") coords '("c")))
(setq currobj (ssadd (entlast) currobj))
(setq coords (list 
(list 5120.5625 820.48) 
(list 5194.585 821.13) 
(list 5194.585 821.307) 
(list 5120.5625 820.557)))
(apply 'command (append '("pline") coords '("c")))
(setq currobj (ssadd (entlast) currobj))
(setq coords (list 
(list 5119.4375 820.557) 
(list 5045.415 821.307) 
(list 5045.415 821.13) 
(list 5119.4375 820.48)))
(apply 'command (append '("pline") coords '("c")))
(setq currobj (ssadd (entlast) currobj))
(setq coords (list 
(list 5119.4375 820.337) 
(list 5045.415 820.987) 
(list 5045.415 820.81) 
(list 5119.4375 820.26)))
(apply 'command (append '("pline") coords '("c")))
(setq currobj (ssadd (entlast) currobj))
(setq coords (list 
(list 5119.4375 820.117) 
(list 5045.415 820.667) 
(list 5045.415 820.49) 
(list 5119.4375 820.04)))
(apply 'command (append '("pline") coords '("c")))
(setq currobj (ssadd (entlast) currobj))
(setq coords (list 
(list 5119.4375 819.897) 
(list 5045.415 820.347) 
(list 5045.415 820.17) 
(list 5119.4375 819.82)))
(apply 'command (append '("pline") coords '("c")))
(setq currobj (ssadd (entlast) currobj))
(setq coords (list 
(list 5119.4375 819.677) 
(list 5045.415 820.027) 
(list 5045.415 819.85) 
(list 5119.4375 819.6)))
(apply 'command (append '("pline") coords '("c")))
(setq currobj (ssadd (entlast) currobj))
(setq coords (list 
(list 5119.4375 819.457) 
(list 5045.415 819.707) 
(list 5045.415 819.53) 
(list 5119.4375 819.38)))
(apply 'command (append '("pline") coords '("c")))
(setq currobj (ssadd (entlast) currobj))
(setq coords (list 
(list 5119.4375 819.237) 
(list 5045.415 819.387) 
(list 5045.415 819.21) 
(list 5119.4375 819.16)))
(apply 'command (append '("pline") coords '("c")))
(setq currobj (ssadd (entlast) currobj))
(setq coords (list 
(list 5119.4375 819.017) 
(list 5045.415 819.067) 
(list 5045.415 818.89) 
(list 5119.4375 818.94)))
(apply 'command (append '("pline") coords '("c")))
(setq currobj (ssadd (entlast) currobj))
(setq coords (list 
(list 5119.4375 818.797) 
(list 5045.415 818.747) 
(list 5045.415 818.57) 
(list 5119.4375 818.72)))
(apply 'command (append '("pline") coords '("c")))
(setq currobj (ssadd (entlast) currobj))
(setq coords (list 
(list 5119.4375 818.577) 
(list 5045.415 818.427) 
(list 5045.415 818.25) 
(list 5119.4375 818.5)))
(apply 'command (append '("pline") coords '("c")))
(setq currobj (ssadd (entlast) currobj))
(setq coords (list 
(list 5119.4375 818.357) 
(list 5045.415 818.107) 
(list 5045.415 817.93) 
(list 5119.4375 818.28)))
(apply 'command (append '("pline") coords '("c")))
(setq currobj (ssadd (entlast) currobj))
(setq coords (list 
(list 5119.4375 818.137) 
(list 5045.415 817.787) 
(list 5045.415 817.61) 
(list 5119.4375 818.06)))
(apply 'command (append '("pline") coords '("c")))
(setq currobj (ssadd (entlast) currobj))
(setq coords (list 
(list 5119.4375 817.917) 
(list 5045.415 817.467) 
(list 5045.415 817.29) 
(list 5119.4375 817.84)))
(apply 'command (append '("pline") coords '("c")))
(setq currobj (ssadd (entlast) currobj))
(setq coords (list 
(list 5119.4375 817.697) 
(list 5045.415 817.147) 
(list 5045.415 816.97) 
(list 5119.4375 817.62)))
(apply 'command (append '("pline") coords '("c")))
(setq currobj (ssadd (entlast) currobj))
(setq coords (list 
(list 5119.4375 817.477) 
(list 5045.415 816.827) 
(list 5045.415 816.65) 
(list 5119.4375 817.4)))
(apply 'command (append '("pline") coords '("c")))
(setq currobj (ssadd (entlast) currobj))
(command "_layer" "set" "nitride" "")
(command "_layer" "set" "text" "")
(command "_circle" "5119.0625,806.257" "0.075")
(command "_circle" "5119.0625,806.557" "0.075")
(command "_circle" "5119.0625,806.857" "0.075")
(command "_circle" "5119.0625,807.157" "0.075")
(command "_circle" "5119.0625,807.457" "0.075")
(command "_circle" "5118.7625,806.257" "0.075")
(command "_circle" "5118.7625,806.557" "0.075")
(command "_circle" "5118.7625,806.857" "0.075")
(command "_circle" "5118.7625,807.157" "0.075")
(command "_circle" "5118.7625,807.457" "0.075")
(command "_circle" "5118.4625,806.257" "0.075")
(command "_circle" "5118.4625,806.557" "0.075")
(command "_circle" "5118.4625,806.857" "0.075")
(command "_circle" "5118.4625,807.157" "0.075")
(command "_circle" "5118.4625,807.457" "0.075")
(command "_circle" "5118.1625,806.257" "0.075")
(command "_circle" "5118.1625,806.557" "0.075")
(command "_circle" "5118.1625,806.857" "0.075")
(command "_circle" "5118.1625,807.157" "0.075")
(command "_circle" "5118.1625,807.457" "0.075")
(command "_circle" "5117.8625,806.257" "0.075")
(command "_circle" "5117.8625,806.557" "0.075")
(command "_circle" "5117.8625,806.857" "0.075")
(command "_circle" "5117.8625,807.157" "0.075")
(command "_circle" "5117.8625,807.457" "0.075")
(command "_layer" "set" "nitride" "")
(setq coords (list 
(list 5120.2625 831.7) 
(list 5120.2625 836.7) 
(list 5119.7375 836.7) 
(list 5119.7375 831.7)))
(apply 'command (append '("pline") coords '("c")))
(setq currobj (ssadd (entlast) currobj))
(command "_layer" "set" "prebias" "")
(command "_rectangle" "5119.7375,831.7" "5120.2625,836.7")
(setq currobj (ssadd (entlast) currobj))
(command "_layer" "set" "nitride" "")
(setq cooledsinglenanobeam16 currobj)
(setq currobj nil)
(setq currobj (ssadd))
; DRAWING PHOTONIC CRYSTAL
(command "_layer" "set" "negYjunc" "")
(setq coords (list 
(list 5120.135 866.7) 
(list 5120 851.7) 
(list 5120 866.7)))
(apply 'command (append '("pline") coords '("c")))
(setq currobj (ssadd (entlast) currobj))
(setq coords (list 
(list 5120.2625 836.7) 
(list 5120.415 866.7) 
(list 5121.126 866.7) 
(list 5121.126 836.7)))
(apply 'command (append '("pline") coords '("c")))
(setq currobj (ssadd (entlast) currobj))
(setq coords (list 
(list 5119.865 866.7) 
(list 5120 851.7) 
(list 5120 866.7)))
(apply 'command (append '("pline") coords '("c")))
(setq currobj (ssadd (entlast) currobj))
(setq coords (list 
(list 5119.7375 836.7) 
(list 5119.585 866.7) 
(list 5118.874 866.7) 
(list 5118.874 836.7)))
(apply 'command (append '("pline") coords '("c")))
(setq currobj (ssadd (entlast) currobj))
(command "_layer" "set" "nitride" "")
(setq yjunction16 currobj)
(setq currobj nil)
(setq currobj (ssadd))
(setq tap16 nil)
(setq tap16 (ssadd))
(command "_layer" "set" "phc" "")
(setq coords (list 
(list 5120 866.7) 
(list 5120.135 866.7) 
(list 5120.135 866.7103) 
(list 5120.135 866.7206) 
(list 5120.135 866.7308) 
(list 5120.135 866.7411) 
(list 5120.135 866.7514) 
(list 5120.135 866.7617) 
(list 5120.135 866.7719) 
(list 5120.135 866.7822) 
(list 5120.135 866.7925) 
(list 5120.135 866.8028) 
(list 5120.135 866.8131) 
(list 5120.135 866.8233) 
(list 5120.135 866.8336) 
(list 5120.135 866.8439) 
(list 5120.135 866.8542) 
(list 5120.135 866.8644) 
(list 5120.135 866.8747) 
(list 5120.135 866.885) 
(list 5120.135 866.8953) 
(list 5120.135 866.9056) 
(list 5120.135 866.9158) 
(list 5120.135 866.9261) 
(list 5120.135 866.9364) 
(list 5120.135 866.9467) 
(list 5120.135 866.9569) 
(list 5120.135 866.9672) 
(list 5120.135 866.9775) 
(list 5120.135 866.9878) 
(list 5120.135 866.9981) 
(list 5120.135 867.0083) 
(list 5120.135 867.0186) 
(list 5120.135 867.0289) 
(list 5120.135 867.0392) 
(list 5120.135 867.0494) 
(list 5120.135 867.0597) 
(list 5120.135 867.07) 
(list 5120 867.07)))
(apply 'command (append '("pline") coords '("c")))
(setq tap16 (ssadd (entlast) tap16))
(command "_mirror" (entlast) "" "5120,900" "5120,901" "No")
(setq tap16 (ssadd (entlast) tap16))
(setq coords (list 
(list 5120.4249 866.7) 
(list 5120.415 866.7) 
(list 5120.4153 866.7103) 
(list 5120.4155 866.7206) 
(list 5120.4157 866.7308) 
(list 5120.4159 866.7411) 
(list 5120.4159 866.7514) 
(list 5120.4159 866.7617) 
(list 5120.4158 866.7719) 
(list 5120.4155 866.7822) 
(list 5120.4152 866.7925) 
(list 5120.4148 866.8028) 
(list 5120.4143 866.8131) 
(list 5120.4137 866.8233) 
(list 5120.4131 866.8336) 
(list 5120.4126 866.8439) 
(list 5120.412 866.8542) 
(list 5120.4115 866.8644) 
(list 5120.4111 866.8747) 
(list 5120.4108 866.885) 
(list 5120.4106 866.8953) 
(list 5120.4106 866.9056) 
(list 5120.4108 866.9158) 
(list 5120.4112 866.9261) 
(list 5120.4117 866.9364) 
(list 5120.4124 866.9467) 
(list 5120.4133 866.9569) 
(list 5120.4144 866.9672) 
(list 5120.4155 866.9775) 
(list 5120.4168 866.9878) 
(list 5120.4181 866.9981) 
(list 5120.4194 867.0083) 
(list 5120.4207 867.0186) 
(list 5120.4219 867.0289) 
(list 5120.4229 867.0392) 
(list 5120.4238 867.0494) 
(list 5120.4245 867.0597) 
(list 5120.4249 867.07) 
(list 5120.4249 867.07)))
(apply 'command (append '("pline") coords '("c")))
(setq tap16 (ssadd (entlast) tap16))
(command "_mirror" (entlast) "" "5120,900" "5120,901" "No")
(setq tap16 (ssadd (entlast) tap16))
(setq coords (list 
(list 5121.126 866.7) 
(list 5120.4249 866.7) 
(list 5120.4249 866.7103) 
(list 5120.4249 866.7206) 
(list 5120.4249 866.7308) 
(list 5120.4249 866.7411) 
(list 5120.4249 866.7514) 
(list 5120.4249 866.7617) 
(list 5120.4249 866.7719) 
(list 5120.4249 866.7822) 
(list 5120.4249 866.7925) 
(list 5120.4249 866.8028) 
(list 5120.4249 866.8131) 
(list 5120.4249 866.8233) 
(list 5120.4249 866.8336) 
(list 5120.4249 866.8439) 
(list 5120.4249 866.8542) 
(list 5120.4249 866.8644) 
(list 5120.4249 866.8747) 
(list 5120.4249 866.885) 
(list 5120.4249 866.8953) 
(list 5120.4249 866.9056) 
(list 5120.4249 866.9158) 
(list 5120.4249 866.9261) 
(list 5120.4249 866.9364) 
(list 5120.4249 866.9467) 
(list 5120.4249 866.9569) 
(list 5120.4249 866.9672) 
(list 5120.4249 866.9775) 
(list 5120.4249 866.9878) 
(list 5120.4249 866.9981) 
(list 5120.4249 867.0083) 
(list 5120.4249 867.0186) 
(list 5120.4249 867.0289) 
(list 5120.4249 867.0392) 
(list 5120.4249 867.0494) 
(list 5120.4249 867.0597) 
(list 5120.4249 867.07) 
(list 5121.126 867.07)))
(apply 'command (append '("pline") coords '("c")))
(setq tap16 (ssadd (entlast) tap16))
(command "_mirror" (entlast) "" "5120,900" "5120,901" "No")
(setq tap16 (ssadd (entlast) tap16))
(setq coords (list 
(list 5120 867.07) 
(list 5120.135 867.07) 
(list 5120.135 867.0803) 
(list 5120.135 867.0906) 
(list 5120.135 867.1008) 
(list 5120.135 867.1111) 
(list 5120.135 867.1214) 
(list 5120.135 867.1317) 
(list 5120.135 867.1419) 
(list 5120.135 867.1522) 
(list 5120.135 867.1625) 
(list 5120.135 867.1728) 
(list 5120.135 867.1831) 
(list 5120.135 867.1933) 
(list 5120.135 867.2036) 
(list 5120.135 867.2139) 
(list 5120.135 867.2242) 
(list 5120.135 867.2344) 
(list 5120.135 867.2447) 
(list 5120.135 867.255) 
(list 5120.135 867.2653) 
(list 5120.135 867.2756) 
(list 5120.135 867.2858) 
(list 5120.135 867.2961) 
(list 5120.135 867.3064) 
(list 5120.135 867.3167) 
(list 5120.135 867.3269) 
(list 5120.135 867.3372) 
(list 5120.135 867.3475) 
(list 5120.135 867.3578) 
(list 5120.135 867.3681) 
(list 5120.135 867.3783) 
(list 5120.135 867.3886) 
(list 5120.135 867.3989) 
(list 5120.135 867.4092) 
(list 5120.135 867.4194) 
(list 5120.135 867.4297) 
(list 5120.135 867.44) 
(list 5120 867.44)))
(apply 'command (append '("pline") coords '("c")))
(setq tap16 (ssadd (entlast) tap16))
(command "_mirror" (entlast) "" "5120,900" "5120,901" "No")
(setq tap16 (ssadd (entlast) tap16))
(setq coords (list 
(list 5120.4347 867.07) 
(list 5120.4249 867.07) 
(list 5120.425 867.0803) 
(list 5120.4248 867.0906) 
(list 5120.4244 867.1008) 
(list 5120.4236 867.1111) 
(list 5120.4225 867.1214) 
(list 5120.4212 867.1317) 
(list 5120.4196 867.1419) 
(list 5120.4178 867.1522) 
(list 5120.4159 867.1625) 
(list 5120.4139 867.1728) 
(list 5120.4119 867.1831) 
(list 5120.4099 867.1933) 
(list 5120.408 867.2036) 
(list 5120.4063 867.2139) 
(list 5120.4048 867.2242) 
(list 5120.4037 867.2344) 
(list 5120.4028 867.2447) 
(list 5120.4024 867.255) 
(list 5120.4024 867.2653) 
(list 5120.4028 867.2756) 
(list 5120.4036 867.2858) 
(list 5120.4049 867.2961) 
(list 5120.4066 867.3064) 
(list 5120.4086 867.3167) 
(list 5120.411 867.3269) 
(list 5120.4135 867.3372) 
(list 5120.4163 867.3475) 
(list 5120.4191 867.3578) 
(list 5120.422 867.3681) 
(list 5120.4247 867.3783) 
(list 5120.4273 867.3886) 
(list 5120.4296 867.3989) 
(list 5120.4316 867.4092) 
(list 5120.4331 867.4194) 
(list 5120.4342 867.4297) 
(list 5120.4347 867.44) 
(list 5120.4347 867.44)))
(apply 'command (append '("pline") coords '("c")))
(setq tap16 (ssadd (entlast) tap16))
(command "_mirror" (entlast) "" "5120,900" "5120,901" "No")
(setq tap16 (ssadd (entlast) tap16))
(setq coords (list 
(list 5121.126 867.07) 
(list 5120.4347 867.07) 
(list 5120.4347 867.0803) 
(list 5120.4347 867.0906) 
(list 5120.4347 867.1008) 
(list 5120.4347 867.1111) 
(list 5120.4347 867.1214) 
(list 5120.4347 867.1317) 
(list 5120.4347 867.1419) 
(list 5120.4347 867.1522) 
(list 5120.4347 867.1625) 
(list 5120.4347 867.1728) 
(list 5120.4347 867.1831) 
(list 5120.4347 867.1933) 
(list 5120.4347 867.2036) 
(list 5120.4347 867.2139) 
(list 5120.4347 867.2242) 
(list 5120.4347 867.2344) 
(list 5120.4347 867.2447) 
(list 5120.4347 867.255) 
(list 5120.4347 867.2653) 
(list 5120.4347 867.2756) 
(list 5120.4347 867.2858) 
(list 5120.4347 867.2961) 
(list 5120.4347 867.3064) 
(list 5120.4347 867.3167) 
(list 5120.4347 867.3269) 
(list 5120.4347 867.3372) 
(list 5120.4347 867.3475) 
(list 5120.4347 867.3578) 
(list 5120.4347 867.3681) 
(list 5120.4347 867.3783) 
(list 5120.4347 867.3886) 
(list 5120.4347 867.3989) 
(list 5120.4347 867.4092) 
(list 5120.4347 867.4194) 
(list 5120.4347 867.4297) 
(list 5120.4347 867.44) 
(list 5121.126 867.44)))
(apply 'command (append '("pline") coords '("c")))
(setq tap16 (ssadd (entlast) tap16))
(command "_mirror" (entlast) "" "5120,900" "5120,901" "No")
(setq tap16 (ssadd (entlast) tap16))
(setq coords (list 
(list 5120 867.44) 
(list 5120.135 867.44) 
(list 5120.135 867.4503) 
(list 5120.135 867.4606) 
(list 5120.135 867.4708) 
(list 5120.135 867.4811) 
(list 5120.135 867.4914) 
(list 5120.135 867.5017) 
(list 5120.135 867.5119) 
(list 5120.135 867.5222) 
(list 5120.135 867.5325) 
(list 5120.135 867.5428) 
(list 5120.135 867.5531) 
(list 5120.135 867.5633) 
(list 5120.135 867.5736) 
(list 5120.135 867.5839) 
(list 5120.135 867.5942) 
(list 5120.135 867.6044) 
(list 5120.135 867.6147) 
(list 5120.135 867.625) 
(list 5120.135 867.6353) 
(list 5120.135 867.6456) 
(list 5120.135 867.6558) 
(list 5120.135 867.6661) 
(list 5120.135 867.6764) 
(list 5120.135 867.6867) 
(list 5120.135 867.6969) 
(list 5120.135 867.7072) 
(list 5120.135 867.7175) 
(list 5120.135 867.7278) 
(list 5120.135 867.7381) 
(list 5120.135 867.7483) 
(list 5120.135 867.7586) 
(list 5120.135 867.7689) 
(list 5120.135 867.7792) 
(list 5120.135 867.7894) 
(list 5120.135 867.7997) 
(list 5120.135 867.81) 
(list 5120 867.81)))
(apply 'command (append '("pline") coords '("c")))
(setq tap16 (ssadd (entlast) tap16))
(command "_mirror" (entlast) "" "5120,900" "5120,901" "No")
(setq tap16 (ssadd (entlast) tap16))
(setq coords (list 
(list 5120.4446 867.44) 
(list 5120.4347 867.44) 
(list 5120.4347 867.4503) 
(list 5120.4341 867.4606) 
(list 5120.433 867.4708) 
(list 5120.4313 867.4811) 
(list 5120.4291 867.4914) 
(list 5120.4265 867.5017) 
(list 5120.4235 867.5119) 
(list 5120.4202 867.5222) 
(list 5120.4167 867.5325) 
(list 5120.4131 867.5428) 
(list 5120.4095 867.5531) 
(list 5120.4061 867.5633) 
(list 5120.4029 867.5736) 
(list 5120.4 867.5839) 
(list 5120.3977 867.5942) 
(list 5120.3958 867.6044) 
(list 5120.3946 867.6147) 
(list 5120.394 867.625) 
(list 5120.3941 867.6353) 
(list 5120.3949 867.6456) 
(list 5120.3965 867.6558) 
(list 5120.3986 867.6661) 
(list 5120.4014 867.6764) 
(list 5120.4048 867.6867) 
(list 5120.4086 867.6969) 
(list 5120.4127 867.7072) 
(list 5120.417 867.7175) 
(list 5120.4214 867.7278) 
(list 5120.4258 867.7381) 
(list 5120.43 867.7483) 
(list 5120.4339 867.7586) 
(list 5120.4373 867.7689) 
(list 5120.4402 867.7792) 
(list 5120.4424 867.7894) 
(list 5120.4439 867.7997) 
(list 5120.4446 867.81) 
(list 5120.4446 867.81)))
(apply 'command (append '("pline") coords '("c")))
(setq tap16 (ssadd (entlast) tap16))
(command "_mirror" (entlast) "" "5120,900" "5120,901" "No")
(setq tap16 (ssadd (entlast) tap16))
(setq coords (list 
(list 5121.126 867.44) 
(list 5120.4446 867.44) 
(list 5120.4446 867.4503) 
(list 5120.4446 867.4606) 
(list 5120.4446 867.4708) 
(list 5120.4446 867.4811) 
(list 5120.4446 867.4914) 
(list 5120.4446 867.5017) 
(list 5120.4446 867.5119) 
(list 5120.4446 867.5222) 
(list 5120.4446 867.5325) 
(list 5120.4446 867.5428) 
(list 5120.4446 867.5531) 
(list 5120.4446 867.5633) 
(list 5120.4446 867.5736) 
(list 5120.4446 867.5839) 
(list 5120.4446 867.5942) 
(list 5120.4446 867.6044) 
(list 5120.4446 867.6147) 
(list 5120.4446 867.625) 
(list 5120.4446 867.6353) 
(list 5120.4446 867.6456) 
(list 5120.4446 867.6558) 
(list 5120.4446 867.6661) 
(list 5120.4446 867.6764) 
(list 5120.4446 867.6867) 
(list 5120.4446 867.6969) 
(list 5120.4446 867.7072) 
(list 5120.4446 867.7175) 
(list 5120.4446 867.7278) 
(list 5120.4446 867.7381) 
(list 5120.4446 867.7483) 
(list 5120.4446 867.7586) 
(list 5120.4446 867.7689) 
(list 5120.4446 867.7792) 
(list 5120.4446 867.7894) 
(list 5120.4446 867.7997) 
(list 5120.4446 867.81) 
(list 5121.126 867.81)))
(apply 'command (append '("pline") coords '("c")))
(setq tap16 (ssadd (entlast) tap16))
(command "_mirror" (entlast) "" "5120,900" "5120,901" "No")
(setq tap16 (ssadd (entlast) tap16))
(setq coords (list 
(list 5120 867.81) 
(list 5120.135 867.81) 
(list 5120.135 867.8203) 
(list 5120.135 867.8306) 
(list 5120.135 867.8408) 
(list 5120.135 867.8511) 
(list 5120.135 867.8614) 
(list 5120.135 867.8717) 
(list 5120.135 867.8819) 
(list 5120.135 867.8922) 
(list 5120.135 867.9025) 
(list 5120.135 867.9128) 
(list 5120.135 867.9231) 
(list 5120.135 867.9333) 
(list 5120.135 867.9436) 
(list 5120.135 867.9539) 
(list 5120.135 867.9642) 
(list 5120.135 867.9744) 
(list 5120.135 867.9847) 
(list 5120.135 867.995) 
(list 5120.135 868.0053) 
(list 5120.135 868.0156) 
(list 5120.135 868.0258) 
(list 5120.135 868.0361) 
(list 5120.135 868.0464) 
(list 5120.135 868.0567) 
(list 5120.135 868.0669) 
(list 5120.135 868.0772) 
(list 5120.135 868.0875) 
(list 5120.135 868.0978) 
(list 5120.135 868.1081) 
(list 5120.135 868.1183) 
(list 5120.135 868.1286) 
(list 5120.135 868.1389) 
(list 5120.135 868.1492) 
(list 5120.135 868.1594) 
(list 5120.135 868.1697) 
(list 5120.135 868.18) 
(list 5120 868.18)))
(apply 'command (append '("pline") coords '("c")))
(setq tap16 (ssadd (entlast) tap16))
(command "_mirror" (entlast) "" "5120,900" "5120,901" "No")
(setq tap16 (ssadd (entlast) tap16))
(setq coords (list 
(list 5120.4545 867.81) 
(list 5120.4446 867.81) 
(list 5120.4445 867.8203) 
(list 5120.4435 867.8306) 
(list 5120.4416 867.8408) 
(list 5120.439 867.8511) 
(list 5120.4357 867.8614) 
(list 5120.4318 867.8717) 
(list 5120.4273 867.8819) 
(list 5120.4225 867.8922) 
(list 5120.4174 867.9025) 
(list 5120.4122 867.9128) 
(list 5120.4071 867.9231) 
(list 5120.4022 867.9333) 
(list 5120.3977 867.9436) 
(list 5120.3938 867.9539) 
(list 5120.3905 867.9642) 
(list 5120.388 867.9744) 
(list 5120.3863 867.9847) 
(list 5120.3856 867.995) 
(list 5120.3859 868.0053) 
(list 5120.3871 868.0156) 
(list 5120.3893 868.0258) 
(list 5120.3924 868.0361) 
(list 5120.3963 868.0464) 
(list 5120.4009 868.0567) 
(list 5120.4062 868.0669) 
(list 5120.4118 868.0772) 
(list 5120.4177 868.0875) 
(list 5120.4238 868.0978) 
(list 5120.4297 868.1081) 
(list 5120.4353 868.1183) 
(list 5120.4405 868.1286) 
(list 5120.4451 868.1389) 
(list 5120.4489 868.1492) 
(list 5120.4517 868.1594) 
(list 5120.4536 868.1697) 
(list 5120.4545 868.18) 
(list 5120.4545 868.18)))
(apply 'command (append '("pline") coords '("c")))
(setq tap16 (ssadd (entlast) tap16))
(command "_mirror" (entlast) "" "5120,900" "5120,901" "No")
(setq tap16 (ssadd (entlast) tap16))
(setq coords (list 
(list 5121.126 867.81) 
(list 5120.4545 867.81) 
(list 5120.4545 867.8203) 
(list 5120.4545 867.8306) 
(list 5120.4545 867.8408) 
(list 5120.4545 867.8511) 
(list 5120.4545 867.8614) 
(list 5120.4545 867.8717) 
(list 5120.4545 867.8819) 
(list 5120.4545 867.8922) 
(list 5120.4545 867.9025) 
(list 5120.4545 867.9128) 
(list 5120.4545 867.9231) 
(list 5120.4545 867.9333) 
(list 5120.4545 867.9436) 
(list 5120.4545 867.9539) 
(list 5120.4545 867.9642) 
(list 5120.4545 867.9744) 
(list 5120.4545 867.9847) 
(list 5120.4545 867.995) 
(list 5120.4545 868.0053) 
(list 5120.4545 868.0156) 
(list 5120.4545 868.0258) 
(list 5120.4545 868.0361) 
(list 5120.4545 868.0464) 
(list 5120.4545 868.0567) 
(list 5120.4545 868.0669) 
(list 5120.4545 868.0772) 
(list 5120.4545 868.0875) 
(list 5120.4545 868.0978) 
(list 5120.4545 868.1081) 
(list 5120.4545 868.1183) 
(list 5120.4545 868.1286) 
(list 5120.4545 868.1389) 
(list 5120.4545 868.1492) 
(list 5120.4545 868.1594) 
(list 5120.4545 868.1697) 
(list 5120.4545 868.18) 
(list 5121.126 868.18)))
(apply 'command (append '("pline") coords '("c")))
(setq tap16 (ssadd (entlast) tap16))
(command "_mirror" (entlast) "" "5120,900" "5120,901" "No")
(setq tap16 (ssadd (entlast) tap16))
(setq coords (list 
(list 5120 868.18) 
(list 5120.135 868.18) 
(list 5120.135 868.1903) 
(list 5120.135 868.2006) 
(list 5120.135 868.2108) 
(list 5120.135 868.2211) 
(list 5120.135 868.2314) 
(list 5120.135 868.2417) 
(list 5120.135 868.2519) 
(list 5120.135 868.2622) 
(list 5120.135 868.2725) 
(list 5120.135 868.2828) 
(list 5120.135 868.2931) 
(list 5120.135 868.3033) 
(list 5120.135 868.3136) 
(list 5120.135 868.3239) 
(list 5120.135 868.3342) 
(list 5120.135 868.3444) 
(list 5120.135 868.3547) 
(list 5120.135 868.365) 
(list 5120.135 868.3753) 
(list 5120.135 868.3856) 
(list 5120.135 868.3958) 
(list 5120.135 868.4061) 
(list 5120.135 868.4164) 
(list 5120.135 868.4267) 
(list 5120.135 868.4369) 
(list 5120.135 868.4472) 
(list 5120.135 868.4575) 
(list 5120.135 868.4678) 
(list 5120.135 868.4781) 
(list 5120.135 868.4883) 
(list 5120.135 868.4986) 
(list 5120.135 868.5089) 
(list 5120.135 868.5192) 
(list 5120.135 868.5294) 
(list 5120.135 868.5397) 
(list 5120.135 868.55) 
(list 5120 868.55)))
(apply 'command (append '("pline") coords '("c")))
(setq tap16 (ssadd (entlast) tap16))
(command "_mirror" (entlast) "" "5120,900" "5120,901" "No")
(setq tap16 (ssadd (entlast) tap16))
(setq coords (list 
(list 5120.4643 868.18) 
(list 5120.4545 868.18) 
(list 5120.4542 868.1903) 
(list 5120.4528 868.2006) 
(list 5120.4503 868.2108) 
(list 5120.4468 868.2211) 
(list 5120.4423 868.2314) 
(list 5120.4371 868.2417) 
(list 5120.4312 868.2519) 
(list 5120.4248 868.2622) 
(list 5120.4181 868.2725) 
(list 5120.4114 868.2828) 
(list 5120.4047 868.2931) 
(list 5120.3984 868.3033) 
(list 5120.3926 868.3136) 
(list 5120.3875 868.3239) 
(list 5120.3833 868.3342) 
(list 5120.3801 868.3444) 
(list 5120.3781 868.3547) 
(list 5120.3772 868.365) 
(list 5120.3776 868.3753) 
(list 5120.3792 868.3856) 
(list 5120.3821 868.3958) 
(list 5120.3861 868.4061) 
(list 5120.3912 868.4164) 
(list 5120.3971 868.4267) 
(list 5120.4038 868.4369) 
(list 5120.411 868.4472) 
(list 5120.4185 868.4575) 
(list 5120.4261 868.4678) 
(list 5120.4335 868.4781) 
(list 5120.4406 868.4883) 
(list 5120.4471 868.4986) 
(list 5120.4528 868.5089) 
(list 5120.4575 868.5192) 
(list 5120.4611 868.5294) 
(list 5120.4634 868.5397) 
(list 5120.4643 868.55) 
(list 5120.4643 868.55)))
(apply 'command (append '("pline") coords '("c")))
(setq tap16 (ssadd (entlast) tap16))
(command "_mirror" (entlast) "" "5120,900" "5120,901" "No")
(setq tap16 (ssadd (entlast) tap16))
(setq coords (list 
(list 5121.126 868.18) 
(list 5120.4643 868.18) 
(list 5120.4643 868.1903) 
(list 5120.4643 868.2006) 
(list 5120.4643 868.2108) 
(list 5120.4643 868.2211) 
(list 5120.4643 868.2314) 
(list 5120.4643 868.2417) 
(list 5120.4643 868.2519) 
(list 5120.4643 868.2622) 
(list 5120.4643 868.2725) 
(list 5120.4643 868.2828) 
(list 5120.4643 868.2931) 
(list 5120.4643 868.3033) 
(list 5120.4643 868.3136) 
(list 5120.4643 868.3239) 
(list 5120.4643 868.3342) 
(list 5120.4643 868.3444) 
(list 5120.4643 868.3547) 
(list 5120.4643 868.365) 
(list 5120.4643 868.3753) 
(list 5120.4643 868.3856) 
(list 5120.4643 868.3958) 
(list 5120.4643 868.4061) 
(list 5120.4643 868.4164) 
(list 5120.4643 868.4267) 
(list 5120.4643 868.4369) 
(list 5120.4643 868.4472) 
(list 5120.4643 868.4575) 
(list 5120.4643 868.4678) 
(list 5120.4643 868.4781) 
(list 5120.4643 868.4883) 
(list 5120.4643 868.4986) 
(list 5120.4643 868.5089) 
(list 5120.4643 868.5192) 
(list 5120.4643 868.5294) 
(list 5120.4643 868.5397) 
(list 5120.4643 868.55) 
(list 5121.126 868.55)))
(apply 'command (append '("pline") coords '("c")))
(setq tap16 (ssadd (entlast) tap16))
(command "_mirror" (entlast) "" "5120,900" "5120,901" "No")
(setq tap16 (ssadd (entlast) tap16))
(setq coords (list 
(list 5120 868.55) 
(list 5120.135 868.55) 
(list 5120.135 868.5603) 
(list 5120.135 868.5706) 
(list 5120.135 868.5808) 
(list 5120.135 868.5911) 
(list 5120.135 868.6014) 
(list 5120.135 868.6117) 
(list 5120.135 868.6219) 
(list 5120.135 868.6322) 
(list 5120.135 868.6425) 
(list 5120.135 868.6528) 
(list 5120.135 868.6631) 
(list 5120.135 868.6733) 
(list 5120.135 868.6836) 
(list 5120.135 868.6939) 
(list 5120.135 868.7042) 
(list 5120.135 868.7144) 
(list 5120.135 868.7247) 
(list 5120.135 868.735) 
(list 5120.135 868.7453) 
(list 5120.135 868.7556) 
(list 5120.135 868.7658) 
(list 5120.135 868.7761) 
(list 5120.135 868.7864) 
(list 5120.135 868.7967) 
(list 5120.135 868.8069) 
(list 5120.135 868.8172) 
(list 5120.135 868.8275) 
(list 5120.135 868.8378) 
(list 5120.135 868.8481) 
(list 5120.135 868.8583) 
(list 5120.135 868.8686) 
(list 5120.135 868.8789) 
(list 5120.135 868.8892) 
(list 5120.135 868.8994) 
(list 5120.135 868.9097) 
(list 5120.135 868.92) 
(list 5120 868.92)))
(apply 'command (append '("pline") coords '("c")))
(setq tap16 (ssadd (entlast) tap16))
(command "_mirror" (entlast) "" "5120,900" "5120,901" "No")
(setq tap16 (ssadd (entlast) tap16))
(setq coords (list 
(list 5120.4742 868.55) 
(list 5120.4643 868.55) 
(list 5120.4639 868.5603) 
(list 5120.4621 868.5706) 
(list 5120.4589 868.5808) 
(list 5120.4545 868.5911) 
(list 5120.4489 868.6014) 
(list 5120.4424 868.6117) 
(list 5120.435 868.6219) 
(list 5120.4271 868.6322) 
(list 5120.4189 868.6425) 
(list 5120.4105 868.6528) 
(list 5120.4023 868.6631) 
(list 5120.3946 868.6733) 
(list 5120.3875 868.6836) 
(list 5120.3812 868.6939) 
(list 5120.3761 868.7042) 
(list 5120.3723 868.7144) 
(list 5120.3698 868.7247) 
(list 5120.3688 868.735) 
(list 5120.3693 868.7453) 
(list 5120.3714 868.7556) 
(list 5120.3749 868.7658) 
(list 5120.3799 868.7761) 
(list 5120.386 868.7864) 
(list 5120.3933 868.7967) 
(list 5120.4014 868.8069) 
(list 5120.4101 868.8172) 
(list 5120.4192 868.8275) 
(list 5120.4284 868.8378) 
(list 5120.4374 868.8481) 
(list 5120.4459 868.8583) 
(list 5120.4537 868.8686) 
(list 5120.4605 868.8789) 
(list 5120.4661 868.8892) 
(list 5120.4704 868.8994) 
(list 5120.4731 868.9097) 
(list 5120.4742 868.92) 
(list 5120.4742 868.92)))
(apply 'command (append '("pline") coords '("c")))
(setq tap16 (ssadd (entlast) tap16))
(command "_mirror" (entlast) "" "5120,900" "5120,901" "No")
(setq tap16 (ssadd (entlast) tap16))
(setq coords (list 
(list 5121.126 868.55) 
(list 5120.4742 868.55) 
(list 5120.4742 868.5603) 
(list 5120.4742 868.5706) 
(list 5120.4742 868.5808) 
(list 5120.4742 868.5911) 
(list 5120.4742 868.6014) 
(list 5120.4742 868.6117) 
(list 5120.4742 868.6219) 
(list 5120.4742 868.6322) 
(list 5120.4742 868.6425) 
(list 5120.4742 868.6528) 
(list 5120.4742 868.6631) 
(list 5120.4742 868.6733) 
(list 5120.4742 868.6836) 
(list 5120.4742 868.6939) 
(list 5120.4742 868.7042) 
(list 5120.4742 868.7144) 
(list 5120.4742 868.7247) 
(list 5120.4742 868.735) 
(list 5120.4742 868.7453) 
(list 5120.4742 868.7556) 
(list 5120.4742 868.7658) 
(list 5120.4742 868.7761) 
(list 5120.4742 868.7864) 
(list 5120.4742 868.7967) 
(list 5120.4742 868.8069) 
(list 5120.4742 868.8172) 
(list 5120.4742 868.8275) 
(list 5120.4742 868.8378) 
(list 5120.4742 868.8481) 
(list 5120.4742 868.8583) 
(list 5120.4742 868.8686) 
(list 5120.4742 868.8789) 
(list 5120.4742 868.8892) 
(list 5120.4742 868.8994) 
(list 5120.4742 868.9097) 
(list 5120.4742 868.92) 
(list 5121.126 868.92)))
(apply 'command (append '("pline") coords '("c")))
(setq tap16 (ssadd (entlast) tap16))
(command "_mirror" (entlast) "" "5120,900" "5120,901" "No")
(setq tap16 (ssadd (entlast) tap16))
(setq coords (list 
(list 5120 868.92) 
(list 5120.135 868.92) 
(list 5120.135 868.9303) 
(list 5120.135 868.9406) 
(list 5120.135 868.9508) 
(list 5120.135 868.9611) 
(list 5120.135 868.9714) 
(list 5120.135 868.9817) 
(list 5120.135 868.9919) 
(list 5120.135 869.0022) 
(list 5120.135 869.0125) 
(list 5120.135 869.0228) 
(list 5120.135 869.0331) 
(list 5120.135 869.0433) 
(list 5120.135 869.0536) 
(list 5120.135 869.0639) 
(list 5120.135 869.0742) 
(list 5120.135 869.0844) 
(list 5120.135 869.0947) 
(list 5120.135 869.105) 
(list 5120.135 869.1153) 
(list 5120.135 869.1256) 
(list 5120.135 869.1358) 
(list 5120.135 869.1461) 
(list 5120.135 869.1564) 
(list 5120.135 869.1667) 
(list 5120.135 869.1769) 
(list 5120.135 869.1872) 
(list 5120.135 869.1975) 
(list 5120.135 869.2078) 
(list 5120.135 869.2181) 
(list 5120.135 869.2283) 
(list 5120.135 869.2386) 
(list 5120.135 869.2489) 
(list 5120.135 869.2592) 
(list 5120.135 869.2694) 
(list 5120.135 869.2797) 
(list 5120.135 869.29) 
(list 5120 869.29)))
(apply 'command (append '("pline") coords '("c")))
(setq tap16 (ssadd (entlast) tap16))
(command "_mirror" (entlast) "" "5120,900" "5120,901" "No")
(setq tap16 (ssadd (entlast) tap16))
(setq coords (list 
(list 5120.4841 868.92) 
(list 5120.4742 868.92) 
(list 5120.4736 868.9303) 
(list 5120.4714 868.9406) 
(list 5120.4676 868.9508) 
(list 5120.4622 868.9611) 
(list 5120.4555 868.9714) 
(list 5120.4477 868.9817) 
(list 5120.4389 868.9919) 
(list 5120.4294 869.0022) 
(list 5120.4196 869.0125) 
(list 5120.4096 869.0228) 
(list 5120.3999 869.0331) 
(list 5120.3907 869.0433) 
(list 5120.3823 869.0536) 
(list 5120.375 869.0639) 
(list 5120.369 869.0742) 
(list 5120.3644 869.0844) 
(list 5120.3615 869.0947) 
(list 5120.3604 869.105) 
(list 5120.3611 869.1153) 
(list 5120.3635 869.1256) 
(list 5120.3678 869.1358) 
(list 5120.3736 869.1461) 
(list 5120.3809 869.1564) 
(list 5120.3894 869.1667) 
(list 5120.399 869.1769) 
(list 5120.4093 869.1872) 
(list 5120.42 869.1975) 
(list 5120.4307 869.2078) 
(list 5120.4412 869.2181) 
(list 5120.4512 869.2283) 
(list 5120.4603 869.2386) 
(list 5120.4682 869.2489) 
(list 5120.4748 869.2592) 
(list 5120.4797 869.2694) 
(list 5120.4828 869.2797) 
(list 5120.4841 869.29) 
(list 5120.4841 869.29)))
(apply 'command (append '("pline") coords '("c")))
(setq tap16 (ssadd (entlast) tap16))
(command "_mirror" (entlast) "" "5120,900" "5120,901" "No")
(setq tap16 (ssadd (entlast) tap16))
(setq coords (list 
(list 5121.126 868.92) 
(list 5120.4841 868.92) 
(list 5120.4841 868.9303) 
(list 5120.4841 868.9406) 
(list 5120.4841 868.9508) 
(list 5120.4841 868.9611) 
(list 5120.4841 868.9714) 
(list 5120.4841 868.9817) 
(list 5120.4841 868.9919) 
(list 5120.4841 869.0022) 
(list 5120.4841 869.0125) 
(list 5120.4841 869.0228) 
(list 5120.4841 869.0331) 
(list 5120.4841 869.0433) 
(list 5120.4841 869.0536) 
(list 5120.4841 869.0639) 
(list 5120.4841 869.0742) 
(list 5120.4841 869.0844) 
(list 5120.4841 869.0947) 
(list 5120.4841 869.105) 
(list 5120.4841 869.1153) 
(list 5120.4841 869.1256) 
(list 5120.4841 869.1358) 
(list 5120.4841 869.1461) 
(list 5120.4841 869.1564) 
(list 5120.4841 869.1667) 
(list 5120.4841 869.1769) 
(list 5120.4841 869.1872) 
(list 5120.4841 869.1975) 
(list 5120.4841 869.2078) 
(list 5120.4841 869.2181) 
(list 5120.4841 869.2283) 
(list 5120.4841 869.2386) 
(list 5120.4841 869.2489) 
(list 5120.4841 869.2592) 
(list 5120.4841 869.2694) 
(list 5120.4841 869.2797) 
(list 5120.4841 869.29) 
(list 5121.126 869.29)))
(apply 'command (append '("pline") coords '("c")))
(setq tap16 (ssadd (entlast) tap16))
(command "_mirror" (entlast) "" "5120,900" "5120,901" "No")
(setq tap16 (ssadd (entlast) tap16))
(setq coords (list 
(list 5120 869.29) 
(list 5120.135 869.29) 
(list 5120.135 869.3003) 
(list 5120.135 869.3106) 
(list 5120.135 869.3208) 
(list 5120.135 869.3311) 
(list 5120.135 869.3414) 
(list 5120.135 869.3517) 
(list 5120.135 869.3619) 
(list 5120.135 869.3722) 
(list 5120.135 869.3825) 
(list 5120.135 869.3928) 
(list 5120.135 869.4031) 
(list 5120.135 869.4133) 
(list 5120.135 869.4236) 
(list 5120.135 869.4339) 
(list 5120.135 869.4442) 
(list 5120.135 869.4544) 
(list 5120.135 869.4647) 
(list 5120.135 869.475) 
(list 5120.135 869.4853) 
(list 5120.135 869.4956) 
(list 5120.135 869.5058) 
(list 5120.135 869.5161) 
(list 5120.135 869.5264) 
(list 5120.135 869.5367) 
(list 5120.135 869.5469) 
(list 5120.135 869.5572) 
(list 5120.135 869.5675) 
(list 5120.135 869.5778) 
(list 5120.135 869.5881) 
(list 5120.135 869.5983) 
(list 5120.135 869.6086) 
(list 5120.135 869.6189) 
(list 5120.135 869.6292) 
(list 5120.135 869.6394) 
(list 5120.135 869.6497) 
(list 5120.135 869.66) 
(list 5120 869.66)))
(apply 'command (append '("pline") coords '("c")))
(setq tap16 (ssadd (entlast) tap16))
(command "_mirror" (entlast) "" "5120,900" "5120,901" "No")
(setq tap16 (ssadd (entlast) tap16))
(setq coords (list 
(list 5120.4939 869.29) 
(list 5120.4841 869.29) 
(list 5120.4834 869.3003) 
(list 5120.4807 869.3106) 
(list 5120.4762 869.3208) 
(list 5120.47 869.3311) 
(list 5120.4621 869.3414) 
(list 5120.453 869.3517) 
(list 5120.4428 869.3619) 
(list 5120.4318 869.3722) 
(list 5120.4203 869.3825) 
(list 5120.4088 869.3928) 
(list 5120.3975 869.4031) 
(list 5120.3869 869.4133) 
(list 5120.3772 869.4236) 
(list 5120.3687 869.4339) 
(list 5120.3618 869.4442) 
(list 5120.3566 869.4544) 
(list 5120.3533 869.4647) 
(list 5120.352 869.475) 
(list 5120.3528 869.4853) 
(list 5120.3557 869.4956) 
(list 5120.3606 869.5058) 
(list 5120.3673 869.5161) 
(list 5120.3758 869.5264) 
(list 5120.3856 869.5367) 
(list 5120.3966 869.5469) 
(list 5120.4084 869.5572) 
(list 5120.4207 869.5675) 
(list 5120.433 869.5778) 
(list 5120.4451 869.5881) 
(list 5120.4565 869.5983) 
(list 5120.4669 869.6086) 
(list 5120.476 869.6189) 
(list 5120.4834 869.6292) 
(list 5120.489 869.6394) 
(list 5120.4926 869.6497) 
(list 5120.4939 869.66) 
(list 5120.4939 869.66)))
(apply 'command (append '("pline") coords '("c")))
(setq tap16 (ssadd (entlast) tap16))
(command "_mirror" (entlast) "" "5120,900" "5120,901" "No")
(setq tap16 (ssadd (entlast) tap16))
(setq coords (list 
(list 5121.126 869.29) 
(list 5120.4939 869.29) 
(list 5120.4939 869.3003) 
(list 5120.4939 869.3106) 
(list 5120.4939 869.3208) 
(list 5120.4939 869.3311) 
(list 5120.4939 869.3414) 
(list 5120.4939 869.3517) 
(list 5120.4939 869.3619) 
(list 5120.4939 869.3722) 
(list 5120.4939 869.3825) 
(list 5120.4939 869.3928) 
(list 5120.4939 869.4031) 
(list 5120.4939 869.4133) 
(list 5120.4939 869.4236) 
(list 5120.4939 869.4339) 
(list 5120.4939 869.4442) 
(list 5120.4939 869.4544) 
(list 5120.4939 869.4647) 
(list 5120.4939 869.475) 
(list 5120.4939 869.4853) 
(list 5120.4939 869.4956) 
(list 5120.4939 869.5058) 
(list 5120.4939 869.5161) 
(list 5120.4939 869.5264) 
(list 5120.4939 869.5367) 
(list 5120.4939 869.5469) 
(list 5120.4939 869.5572) 
(list 5120.4939 869.5675) 
(list 5120.4939 869.5778) 
(list 5120.4939 869.5881) 
(list 5120.4939 869.5983) 
(list 5120.4939 869.6086) 
(list 5120.4939 869.6189) 
(list 5120.4939 869.6292) 
(list 5120.4939 869.6394) 
(list 5120.4939 869.6497) 
(list 5120.4939 869.66) 
(list 5121.126 869.66)))
(apply 'command (append '("pline") coords '("c")))
(setq tap16 (ssadd (entlast) tap16))
(command "_mirror" (entlast) "" "5120,900" "5120,901" "No")
(setq tap16 (ssadd (entlast) tap16))
(setq coords (list 
(list 5120 869.66) 
(list 5120.135 869.66) 
(list 5120.135 869.6703) 
(list 5120.135 869.6806) 
(list 5120.135 869.6908) 
(list 5120.135 869.7011) 
(list 5120.135 869.7114) 
(list 5120.135 869.7217) 
(list 5120.135 869.7319) 
(list 5120.135 869.7422) 
(list 5120.135 869.7525) 
(list 5120.135 869.7628) 
(list 5120.135 869.7731) 
(list 5120.135 869.7833) 
(list 5120.135 869.7936) 
(list 5120.135 869.8039) 
(list 5120.135 869.8142) 
(list 5120.135 869.8244) 
(list 5120.135 869.8347) 
(list 5120.135 869.845) 
(list 5120.135 869.8553) 
(list 5120.135 869.8656) 
(list 5120.135 869.8758) 
(list 5120.135 869.8861) 
(list 5120.135 869.8964) 
(list 5120.135 869.9067) 
(list 5120.135 869.9169) 
(list 5120.135 869.9272) 
(list 5120.135 869.9375) 
(list 5120.135 869.9478) 
(list 5120.135 869.9581) 
(list 5120.135 869.9683) 
(list 5120.135 869.9786) 
(list 5120.135 869.9889) 
(list 5120.135 869.9992) 
(list 5120.135 870.0094) 
(list 5120.135 870.0197) 
(list 5120.135 870.03) 
(list 5120 870.03)))
(apply 'command (append '("pline") coords '("c")))
(setq tap16 (ssadd (entlast) tap16))
(command "_mirror" (entlast) "" "5120,900" "5120,901" "No")
(setq tap16 (ssadd (entlast) tap16))
(setq coords (list 
(list 5120.5038 869.66) 
(list 5120.4939 869.66) 
(list 5120.4931 869.6703) 
(list 5120.49 869.6806) 
(list 5120.4849 869.6908) 
(list 5120.4777 869.7011) 
(list 5120.4688 869.7114) 
(list 5120.4583 869.7217) 
(list 5120.4466 869.7319) 
(list 5120.4341 869.7422) 
(list 5120.421 869.7525) 
(list 5120.4079 869.7628) 
(list 5120.3951 869.7731) 
(list 5120.3831 869.7833) 
(list 5120.372 869.7936) 
(list 5120.3625 869.8039) 
(list 5120.3546 869.8142) 
(list 5120.3487 869.8244) 
(list 5120.345 869.8347) 
(list 5120.3436 869.845) 
(list 5120.3445 869.8553) 
(list 5120.3478 869.8656) 
(list 5120.3534 869.8758) 
(list 5120.3611 869.8861) 
(list 5120.3706 869.8964) 
(list 5120.3818 869.9067) 
(list 5120.3942 869.9169) 
(list 5120.4076 869.9272) 
(list 5120.4214 869.9375) 
(list 5120.4354 869.9478) 
(list 5120.449 869.9581) 
(list 5120.4618 869.9683) 
(list 5120.4735 869.9786) 
(list 5120.4837 869.9889) 
(list 5120.4921 869.9992) 
(list 5120.4983 870.0094) 
(list 5120.5023 870.0197) 
(list 5120.5038 870.03) 
(list 5120.5038 870.03)))
(apply 'command (append '("pline") coords '("c")))
(setq tap16 (ssadd (entlast) tap16))
(command "_mirror" (entlast) "" "5120,900" "5120,901" "No")
(setq tap16 (ssadd (entlast) tap16))
(setq coords (list 
(list 5121.126 869.66) 
(list 5120.5038 869.66) 
(list 5120.5038 869.6703) 
(list 5120.5038 869.6806) 
(list 5120.5038 869.6908) 
(list 5120.5038 869.7011) 
(list 5120.5038 869.7114) 
(list 5120.5038 869.7217) 
(list 5120.5038 869.7319) 
(list 5120.5038 869.7422) 
(list 5120.5038 869.7525) 
(list 5120.5038 869.7628) 
(list 5120.5038 869.7731) 
(list 5120.5038 869.7833) 
(list 5120.5038 869.7936) 
(list 5120.5038 869.8039) 
(list 5120.5038 869.8142) 
(list 5120.5038 869.8244) 
(list 5120.5038 869.8347) 
(list 5120.5038 869.845) 
(list 5120.5038 869.8553) 
(list 5120.5038 869.8656) 
(list 5120.5038 869.8758) 
(list 5120.5038 869.8861) 
(list 5120.5038 869.8964) 
(list 5120.5038 869.9067) 
(list 5120.5038 869.9169) 
(list 5120.5038 869.9272) 
(list 5120.5038 869.9375) 
(list 5120.5038 869.9478) 
(list 5120.5038 869.9581) 
(list 5120.5038 869.9683) 
(list 5120.5038 869.9786) 
(list 5120.5038 869.9889) 
(list 5120.5038 869.9992) 
(list 5120.5038 870.0094) 
(list 5120.5038 870.0197) 
(list 5120.5038 870.03) 
(list 5121.126 870.03)))
(apply 'command (append '("pline") coords '("c")))
(setq tap16 (ssadd (entlast) tap16))
(command "_mirror" (entlast) "" "5120,900" "5120,901" "No")
(setq tap16 (ssadd (entlast) tap16))
(setq coords (list 
(list 5120 870.03) 
(list 5120.135 870.03) 
(list 5120.135 870.0403) 
(list 5120.135 870.0506) 
(list 5120.135 870.0608) 
(list 5120.135 870.0711) 
(list 5120.135 870.0814) 
(list 5120.135 870.0917) 
(list 5120.135 870.1019) 
(list 5120.135 870.1122) 
(list 5120.135 870.1225) 
(list 5120.135 870.1328) 
(list 5120.135 870.1431) 
(list 5120.135 870.1533) 
(list 5120.135 870.1636) 
(list 5120.135 870.1739) 
(list 5120.135 870.1842) 
(list 5120.135 870.1944) 
(list 5120.135 870.2047) 
(list 5120.135 870.215) 
(list 5120.135 870.2253) 
(list 5120.135 870.2356) 
(list 5120.135 870.2458) 
(list 5120.135 870.2561) 
(list 5120.135 870.2664) 
(list 5120.135 870.2767) 
(list 5120.135 870.2869) 
(list 5120.135 870.2972) 
(list 5120.135 870.3075) 
(list 5120.135 870.3178) 
(list 5120.135 870.3281) 
(list 5120.135 870.3383) 
(list 5120.135 870.3486) 
(list 5120.135 870.3589) 
(list 5120.135 870.3692) 
(list 5120.135 870.3794) 
(list 5120.135 870.3897) 
(list 5120.135 870.4) 
(list 5120 870.4)))
(apply 'command (append '("pline") coords '("c")))
(setq tap16 (ssadd (entlast) tap16))
(command "_mirror" (entlast) "" "5120,900" "5120,901" "No")
(setq tap16 (ssadd (entlast) tap16))
(setq coords (list 
(list 5120.5137 870.03) 
(list 5120.5038 870.03) 
(list 5120.5028 870.0403) 
(list 5120.4994 870.0506) 
(list 5120.4935 870.0608) 
(list 5120.4854 870.0711) 
(list 5120.4754 870.0814) 
(list 5120.4636 870.0917) 
(list 5120.4505 870.1019) 
(list 5120.4364 870.1122) 
(list 5120.4218 870.1225) 
(list 5120.4071 870.1328) 
(list 5120.3928 870.1431) 
(list 5120.3792 870.1533) 
(list 5120.3669 870.1636) 
(list 5120.3562 870.1739) 
(list 5120.3474 870.1842) 
(list 5120.3409 870.1944) 
(list 5120.3367 870.2047) 
(list 5120.3352 870.215) 
(list 5120.3363 870.2253) 
(list 5120.34 870.2356) 
(list 5120.3462 870.2458) 
(list 5120.3548 870.2561) 
(list 5120.3655 870.2664) 
(list 5120.3779 870.2767) 
(list 5120.3918 870.2869) 
(list 5120.4067 870.2972) 
(list 5120.4222 870.3075) 
(list 5120.4377 870.3178) 
(list 5120.4528 870.3281) 
(list 5120.4671 870.3383) 
(list 5120.4801 870.3486) 
(list 5120.4914 870.3589) 
(list 5120.5007 870.3692) 
(list 5120.5076 870.3794) 
(list 5120.512 870.3897) 
(list 5120.5137 870.4) 
(list 5120.5137 870.4)))
(apply 'command (append '("pline") coords '("c")))
(setq tap16 (ssadd (entlast) tap16))
(command "_mirror" (entlast) "" "5120,900" "5120,901" "No")
(setq tap16 (ssadd (entlast) tap16))
(setq coords (list 
(list 5121.126 870.03) 
(list 5120.5137 870.03) 
(list 5120.5137 870.0403) 
(list 5120.5137 870.0506) 
(list 5120.5137 870.0608) 
(list 5120.5137 870.0711) 
(list 5120.5137 870.0814) 
(list 5120.5137 870.0917) 
(list 5120.5137 870.1019) 
(list 5120.5137 870.1122) 
(list 5120.5137 870.1225) 
(list 5120.5137 870.1328) 
(list 5120.5137 870.1431) 
(list 5120.5137 870.1533) 
(list 5120.5137 870.1636) 
(list 5120.5137 870.1739) 
(list 5120.5137 870.1842) 
(list 5120.5137 870.1944) 
(list 5120.5137 870.2047) 
(list 5120.5137 870.215) 
(list 5120.5137 870.2253) 
(list 5120.5137 870.2356) 
(list 5120.5137 870.2458) 
(list 5120.5137 870.2561) 
(list 5120.5137 870.2664) 
(list 5120.5137 870.2767) 
(list 5120.5137 870.2869) 
(list 5120.5137 870.2972) 
(list 5120.5137 870.3075) 
(list 5120.5137 870.3178) 
(list 5120.5137 870.3281) 
(list 5120.5137 870.3383) 
(list 5120.5137 870.3486) 
(list 5120.5137 870.3589) 
(list 5120.5137 870.3692) 
(list 5120.5137 870.3794) 
(list 5120.5137 870.3897) 
(list 5120.5137 870.4) 
(list 5121.126 870.4)))
(apply 'command (append '("pline") coords '("c")))
(setq tap16 (ssadd (entlast) tap16))
(command "_mirror" (entlast) "" "5120,900" "5120,901" "No")
(setq tap16 (ssadd (entlast) tap16))
(setq coords (list 
(list 5120 870.4) 
(list 5120.135 870.4) 
(list 5120.135 870.4103) 
(list 5120.135 870.4206) 
(list 5120.135 870.4308) 
(list 5120.135 870.4411) 
(list 5120.135 870.4514) 
(list 5120.135 870.4617) 
(list 5120.135 870.4719) 
(list 5120.135 870.4822) 
(list 5120.135 870.4925) 
(list 5120.135 870.5028) 
(list 5120.135 870.5131) 
(list 5120.135 870.5233) 
(list 5120.135 870.5336) 
(list 5120.135 870.5439) 
(list 5120.135 870.5542) 
(list 5120.135 870.5644) 
(list 5120.135 870.5747) 
(list 5120.135 870.585) 
(list 5120.135 870.5953) 
(list 5120.135 870.6056) 
(list 5120.135 870.6158) 
(list 5120.135 870.6261) 
(list 5120.135 870.6364) 
(list 5120.135 870.6467) 
(list 5120.135 870.6569) 
(list 5120.135 870.6672) 
(list 5120.135 870.6775) 
(list 5120.135 870.6878) 
(list 5120.135 870.6981) 
(list 5120.135 870.7083) 
(list 5120.135 870.7186) 
(list 5120.135 870.7289) 
(list 5120.135 870.7392) 
(list 5120.135 870.7494) 
(list 5120.135 870.7597) 
(list 5120.135 870.77) 
(list 5120 870.77)))
(apply 'command (append '("pline") coords '("c")))
(setq tap16 (ssadd (entlast) tap16))
(command "_mirror" (entlast) "" "5120,900" "5120,901" "No")
(setq tap16 (ssadd (entlast) tap16))
(setq coords (list 
(list 5120.5235 870.4) 
(list 5120.5137 870.4) 
(list 5120.5125 870.4103) 
(list 5120.5087 870.4206) 
(list 5120.5022 870.4308) 
(list 5120.4932 870.4411) 
(list 5120.482 870.4514) 
(list 5120.4689 870.4617) 
(list 5120.4543 870.4719) 
(list 5120.4387 870.4822) 
(list 5120.4225 870.4925) 
(list 5120.4062 870.5028) 
(list 5120.3904 870.5131) 
(list 5120.3754 870.5233) 
(list 5120.3618 870.5336) 
(list 5120.3499 870.5439) 
(list 5120.3402 870.5542) 
(list 5120.333 870.5644) 
(list 5120.3285 870.5747) 
(list 5120.3268 870.585) 
(list 5120.328 870.5953) 
(list 5120.3321 870.6056) 
(list 5120.339 870.6158) 
(list 5120.3485 870.6261) 
(list 5120.3603 870.6364) 
(list 5120.3741 870.6467) 
(list 5120.3894 870.6569) 
(list 5120.4059 870.6672) 
(list 5120.4229 870.6775) 
(list 5120.44 870.6878) 
(list 5120.4567 870.6981) 
(list 5120.4724 870.7083) 
(list 5120.4867 870.7186) 
(list 5120.4992 870.7289) 
(list 5120.5094 870.7392) 
(list 5120.517 870.7494) 
(list 5120.5217 870.7597) 
(list 5120.5235 870.77) 
(list 5120.5235 870.77)))
(apply 'command (append '("pline") coords '("c")))
(setq tap16 (ssadd (entlast) tap16))
(command "_mirror" (entlast) "" "5120,900" "5120,901" "No")
(setq tap16 (ssadd (entlast) tap16))
(setq coords (list 
(list 5121.126 870.4) 
(list 5120.5235 870.4) 
(list 5120.5235 870.4103) 
(list 5120.5235 870.4206) 
(list 5120.5235 870.4308) 
(list 5120.5235 870.4411) 
(list 5120.5235 870.4514) 
(list 5120.5235 870.4617) 
(list 5120.5235 870.4719) 
(list 5120.5235 870.4822) 
(list 5120.5235 870.4925) 
(list 5120.5235 870.5028) 
(list 5120.5235 870.5131) 
(list 5120.5235 870.5233) 
(list 5120.5235 870.5336) 
(list 5120.5235 870.5439) 
(list 5120.5235 870.5542) 
(list 5120.5235 870.5644) 
(list 5120.5235 870.5747) 
(list 5120.5235 870.585) 
(list 5120.5235 870.5953) 
(list 5120.5235 870.6056) 
(list 5120.5235 870.6158) 
(list 5120.5235 870.6261) 
(list 5120.5235 870.6364) 
(list 5120.5235 870.6467) 
(list 5120.5235 870.6569) 
(list 5120.5235 870.6672) 
(list 5120.5235 870.6775) 
(list 5120.5235 870.6878) 
(list 5120.5235 870.6981) 
(list 5120.5235 870.7083) 
(list 5120.5235 870.7186) 
(list 5120.5235 870.7289) 
(list 5120.5235 870.7392) 
(list 5120.5235 870.7494) 
(list 5120.5235 870.7597) 
(list 5120.5235 870.77) 
(list 5121.126 870.77)))
(apply 'command (append '("pline") coords '("c")))
(setq tap16 (ssadd (entlast) tap16))
(command "_mirror" (entlast) "" "5120,900" "5120,901" "No")
(setq tap16 (ssadd (entlast) tap16))
(setq coords (list 
(list 5120 870.77) 
(list 5120.135 870.77) 
(list 5120.135 870.7803) 
(list 5120.135 870.7906) 
(list 5120.135 870.8008) 
(list 5120.135 870.8111) 
(list 5120.135 870.8214) 
(list 5120.135 870.8317) 
(list 5120.135 870.8419) 
(list 5120.135 870.8522) 
(list 5120.135 870.8625) 
(list 5120.135 870.8728) 
(list 5120.135 870.8831) 
(list 5120.135 870.8933) 
(list 5120.135 870.9036) 
(list 5120.135 870.9139) 
(list 5120.135 870.9242) 
(list 5120.135 870.9344) 
(list 5120.135 870.9447) 
(list 5120.135 870.955) 
(list 5120.135 870.9653) 
(list 5120.135 870.9756) 
(list 5120.135 870.9858) 
(list 5120.135 870.9961) 
(list 5120.135 871.0064) 
(list 5120.135 871.0167) 
(list 5120.135 871.0269) 
(list 5120.135 871.0372) 
(list 5120.135 871.0475) 
(list 5120.135 871.0578) 
(list 5120.135 871.0681) 
(list 5120.135 871.0783) 
(list 5120.135 871.0886) 
(list 5120.135 871.0989) 
(list 5120.135 871.1092) 
(list 5120.135 871.1194) 
(list 5120.135 871.1297) 
(list 5120.135 871.14) 
(list 5120 871.14)))
(apply 'command (append '("pline") coords '("c")))
(setq tap16 (ssadd (entlast) tap16))
(command "_mirror" (entlast) "" "5120,900" "5120,901" "No")
(setq tap16 (ssadd (entlast) tap16))
(setq coords (list 
(list 5120.5334 870.77) 
(list 5120.5235 870.77) 
(list 5120.5223 870.7803) 
(list 5120.518 870.7906) 
(list 5120.5108 870.8008) 
(list 5120.5009 870.8111) 
(list 5120.4886 870.8214) 
(list 5120.4742 870.8317) 
(list 5120.4582 870.8419) 
(list 5120.441 870.8522) 
(list 5120.4232 870.8625) 
(list 5120.4054 870.8728) 
(list 5120.388 870.8831) 
(list 5120.3716 870.8933) 
(list 5120.3566 870.9036) 
(list 5120.3437 870.9139) 
(list 5120.3331 870.9242) 
(list 5120.3252 870.9344) 
(list 5120.3202 870.9447) 
(list 5120.3184 870.955) 
(list 5120.3198 870.9653) 
(list 5120.3243 870.9756) 
(list 5120.3319 870.9858) 
(list 5120.3423 870.9961) 
(list 5120.3552 871.0064) 
(list 5120.3703 871.0167) 
(list 5120.387 871.0269) 
(list 5120.405 871.0372) 
(list 5120.4236 871.0475) 
(list 5120.4423 871.0578) 
(list 5120.4605 871.0681) 
(list 5120.4777 871.0783) 
(list 5120.4933 871.0886) 
(list 5120.5069 871.0989) 
(list 5120.518 871.1092) 
(list 5120.5263 871.1194) 
(list 5120.5315 871.1297) 
(list 5120.5334 871.14) 
(list 5120.5334 871.14)))
(apply 'command (append '("pline") coords '("c")))
(setq tap16 (ssadd (entlast) tap16))
(command "_mirror" (entlast) "" "5120,900" "5120,901" "No")
(setq tap16 (ssadd (entlast) tap16))
(setq coords (list 
(list 5121.126 870.77) 
(list 5120.5334 870.77) 
(list 5120.5334 870.7803) 
(list 5120.5334 870.7906) 
(list 5120.5334 870.8008) 
(list 5120.5334 870.8111) 
(list 5120.5334 870.8214) 
(list 5120.5334 870.8317) 
(list 5120.5334 870.8419) 
(list 5120.5334 870.8522) 
(list 5120.5334 870.8625) 
(list 5120.5334 870.8728) 
(list 5120.5334 870.8831) 
(list 5120.5334 870.8933) 
(list 5120.5334 870.9036) 
(list 5120.5334 870.9139) 
(list 5120.5334 870.9242) 
(list 5120.5334 870.9344) 
(list 5120.5334 870.9447) 
(list 5120.5334 870.955) 
(list 5120.5334 870.9653) 
(list 5120.5334 870.9756) 
(list 5120.5334 870.9858) 
(list 5120.5334 870.9961) 
(list 5120.5334 871.0064) 
(list 5120.5334 871.0167) 
(list 5120.5334 871.0269) 
(list 5120.5334 871.0372) 
(list 5120.5334 871.0475) 
(list 5120.5334 871.0578) 
(list 5120.5334 871.0681) 
(list 5120.5334 871.0783) 
(list 5120.5334 871.0886) 
(list 5120.5334 871.0989) 
(list 5120.5334 871.1092) 
(list 5120.5334 871.1194) 
(list 5120.5334 871.1297) 
(list 5120.5334 871.14) 
(list 5121.126 871.14)))
(apply 'command (append '("pline") coords '("c")))
(setq tap16 (ssadd (entlast) tap16))
(command "_mirror" (entlast) "" "5120,900" "5120,901" "No")
(setq tap16 (ssadd (entlast) tap16))
(setq coords (list 
(list 5120 871.14) 
(list 5120.135 871.14) 
(list 5120.135 871.1503) 
(list 5120.135 871.1606) 
(list 5120.135 871.1708) 
(list 5120.135 871.1811) 
(list 5120.135 871.1914) 
(list 5120.135 871.2017) 
(list 5120.135 871.2119) 
(list 5120.135 871.2222) 
(list 5120.135 871.2325) 
(list 5120.135 871.2428) 
(list 5120.135 871.2531) 
(list 5120.135 871.2633) 
(list 5120.135 871.2736) 
(list 5120.135 871.2839) 
(list 5120.135 871.2942) 
(list 5120.135 871.3044) 
(list 5120.135 871.3147) 
(list 5120.135 871.325) 
(list 5120.135 871.3353) 
(list 5120.135 871.3456) 
(list 5120.135 871.3558) 
(list 5120.135 871.3661) 
(list 5120.135 871.3764) 
(list 5120.135 871.3867) 
(list 5120.135 871.3969) 
(list 5120.135 871.4072) 
(list 5120.135 871.4175) 
(list 5120.135 871.4278) 
(list 5120.135 871.4381) 
(list 5120.135 871.4483) 
(list 5120.135 871.4586) 
(list 5120.135 871.4689) 
(list 5120.135 871.4792) 
(list 5120.135 871.4894) 
(list 5120.135 871.4997) 
(list 5120.135 871.51) 
(list 5120 871.51)))
(apply 'command (append '("pline") coords '("c")))
(setq tap16 (ssadd (entlast) tap16))
(command "_mirror" (entlast) "" "5120,900" "5120,901" "No")
(setq tap16 (ssadd (entlast) tap16))
(setq coords (list 
(list 5120.5433 871.14) 
(list 5120.5334 871.14) 
(list 5120.532 871.1503) 
(list 5120.5273 871.1606) 
(list 5120.5194 871.1708) 
(list 5120.5086 871.1811) 
(list 5120.4952 871.1914) 
(list 5120.4795 871.2017) 
(list 5120.462 871.2119) 
(list 5120.4433 871.2222) 
(list 5120.424 871.2325) 
(list 5120.4045 871.2428) 
(list 5120.3856 871.2531) 
(list 5120.3677 871.2633) 
(list 5120.3515 871.2736) 
(list 5120.3374 871.2839) 
(list 5120.3259 871.2942) 
(list 5120.3173 871.3044) 
(list 5120.312 871.3147) 
(list 5120.31 871.325) 
(list 5120.3115 871.3353) 
(list 5120.3164 871.3456) 
(list 5120.3247 871.3558) 
(list 5120.336 871.3661) 
(list 5120.3501 871.3764) 
(list 5120.3664 871.3867) 
(list 5120.3847 871.3969) 
(list 5120.4042 871.4072) 
(list 5120.4244 871.4175) 
(list 5120.4446 871.4278) 
(list 5120.4644 871.4381) 
(list 5120.483 871.4483) 
(list 5120.4999 871.4586) 
(list 5120.5146 871.4689) 
(list 5120.5266 871.4792) 
(list 5120.5356 871.4894) 
(list 5120.5412 871.4997) 
(list 5120.5433 871.51) 
(list 5120.5433 871.51)))
(apply 'command (append '("pline") coords '("c")))
(setq tap16 (ssadd (entlast) tap16))
(command "_mirror" (entlast) "" "5120,900" "5120,901" "No")
(setq tap16 (ssadd (entlast) tap16))
(setq coords (list 
(list 5121.126 871.14) 
(list 5120.5433 871.14) 
(list 5120.5433 871.1503) 
(list 5120.5433 871.1606) 
(list 5120.5433 871.1708) 
(list 5120.5433 871.1811) 
(list 5120.5433 871.1914) 
(list 5120.5433 871.2017) 
(list 5120.5433 871.2119) 
(list 5120.5433 871.2222) 
(list 5120.5433 871.2325) 
(list 5120.5433 871.2428) 
(list 5120.5433 871.2531) 
(list 5120.5433 871.2633) 
(list 5120.5433 871.2736) 
(list 5120.5433 871.2839) 
(list 5120.5433 871.2942) 
(list 5120.5433 871.3044) 
(list 5120.5433 871.3147) 
(list 5120.5433 871.325) 
(list 5120.5433 871.3353) 
(list 5120.5433 871.3456) 
(list 5120.5433 871.3558) 
(list 5120.5433 871.3661) 
(list 5120.5433 871.3764) 
(list 5120.5433 871.3867) 
(list 5120.5433 871.3969) 
(list 5120.5433 871.4072) 
(list 5120.5433 871.4175) 
(list 5120.5433 871.4278) 
(list 5120.5433 871.4381) 
(list 5120.5433 871.4483) 
(list 5120.5433 871.4586) 
(list 5120.5433 871.4689) 
(list 5120.5433 871.4792) 
(list 5120.5433 871.4894) 
(list 5120.5433 871.4997) 
(list 5120.5433 871.51) 
(list 5121.126 871.51)))
(apply 'command (append '("pline") coords '("c")))
(setq tap16 (ssadd (entlast) tap16))
(command "_mirror" (entlast) "" "5120,900" "5120,901" "No")
(setq tap16 (ssadd (entlast) tap16))
(setq coords (list 
(list 5120 871.51) 
(list 5120.135 871.51) 
(list 5120.135 871.5203) 
(list 5120.135 871.5306) 
(list 5120.135 871.5408) 
(list 5120.135 871.5511) 
(list 5120.135 871.5614) 
(list 5120.135 871.5717) 
(list 5120.135 871.5819) 
(list 5120.135 871.5922) 
(list 5120.135 871.6025) 
(list 5120.135 871.6128) 
(list 5120.135 871.6231) 
(list 5120.135 871.6333) 
(list 5120.135 871.6436) 
(list 5120.135 871.6539) 
(list 5120.135 871.6642) 
(list 5120.135 871.6744) 
(list 5120.135 871.6847) 
(list 5120.135 871.695) 
(list 5120.135 871.7053) 
(list 5120.135 871.7156) 
(list 5120.135 871.7258) 
(list 5120.135 871.7361) 
(list 5120.135 871.7464) 
(list 5120.135 871.7567) 
(list 5120.135 871.7669) 
(list 5120.135 871.7772) 
(list 5120.135 871.7875) 
(list 5120.135 871.7978) 
(list 5120.135 871.8081) 
(list 5120.135 871.8183) 
(list 5120.135 871.8286) 
(list 5120.135 871.8389) 
(list 5120.135 871.8492) 
(list 5120.135 871.8594) 
(list 5120.135 871.8697) 
(list 5120.135 871.88) 
(list 5120 871.88)))
(apply 'command (append '("pline") coords '("c")))
(setq tap16 (ssadd (entlast) tap16))
(command "_mirror" (entlast) "" "5120,900" "5120,901" "No")
(setq tap16 (ssadd (entlast) tap16))
(setq coords (list 
(list 5120.5531 871.51) 
(list 5120.5433 871.51) 
(list 5120.5417 871.5203) 
(list 5120.5366 871.5306) 
(list 5120.5281 871.5408) 
(list 5120.5163 871.5511) 
(list 5120.5018 871.5614) 
(list 5120.4848 871.5717) 
(list 5120.4659 871.5819) 
(list 5120.4457 871.5922) 
(list 5120.4247 871.6025) 
(list 5120.4037 871.6128) 
(list 5120.3832 871.6231) 
(list 5120.3639 871.6333) 
(list 5120.3464 871.6436) 
(list 5120.3311 871.6539) 
(list 5120.3187 871.6642) 
(list 5120.3095 871.6744) 
(list 5120.3037 871.6847) 
(list 5120.3016 871.695) 
(list 5120.3032 871.7053) 
(list 5120.3086 871.7156) 
(list 5120.3175 871.7258) 
(list 5120.3298 871.7361) 
(list 5120.3449 871.7464) 
(list 5120.3626 871.7567) 
(list 5120.3823 871.7669) 
(list 5120.4033 871.7772) 
(list 5120.4251 871.7875) 
(list 5120.447 871.7978) 
(list 5120.4682 871.8081) 
(list 5120.4883 871.8183) 
(list 5120.5065 871.8286) 
(list 5120.5224 871.8389) 
(list 5120.5353 871.8492) 
(list 5120.5449 871.8594) 
(list 5120.5509 871.8697) 
(list 5120.5531 871.88) 
(list 5120.5531 871.88)))
(apply 'command (append '("pline") coords '("c")))
(setq tap16 (ssadd (entlast) tap16))
(command "_mirror" (entlast) "" "5120,900" "5120,901" "No")
(setq tap16 (ssadd (entlast) tap16))
(setq coords (list 
(list 5121.126 871.51) 
(list 5120.5531 871.51) 
(list 5120.5531 871.5203) 
(list 5120.5531 871.5306) 
(list 5120.5531 871.5408) 
(list 5120.5531 871.5511) 
(list 5120.5531 871.5614) 
(list 5120.5531 871.5717) 
(list 5120.5531 871.5819) 
(list 5120.5531 871.5922) 
(list 5120.5531 871.6025) 
(list 5120.5531 871.6128) 
(list 5120.5531 871.6231) 
(list 5120.5531 871.6333) 
(list 5120.5531 871.6436) 
(list 5120.5531 871.6539) 
(list 5120.5531 871.6642) 
(list 5120.5531 871.6744) 
(list 5120.5531 871.6847) 
(list 5120.5531 871.695) 
(list 5120.5531 871.7053) 
(list 5120.5531 871.7156) 
(list 5120.5531 871.7258) 
(list 5120.5531 871.7361) 
(list 5120.5531 871.7464) 
(list 5120.5531 871.7567) 
(list 5120.5531 871.7669) 
(list 5120.5531 871.7772) 
(list 5120.5531 871.7875) 
(list 5120.5531 871.7978) 
(list 5120.5531 871.8081) 
(list 5120.5531 871.8183) 
(list 5120.5531 871.8286) 
(list 5120.5531 871.8389) 
(list 5120.5531 871.8492) 
(list 5120.5531 871.8594) 
(list 5120.5531 871.8697) 
(list 5120.5531 871.88) 
(list 5121.126 871.88)))
(apply 'command (append '("pline") coords '("c")))
(setq tap16 (ssadd (entlast) tap16))
(command "_mirror" (entlast) "" "5120,900" "5120,901" "No")
(setq tap16 (ssadd (entlast) tap16))
(setq coords (list 
(list 5120 871.88) 
(list 5120.135 871.88) 
(list 5120.135 871.8903) 
(list 5120.135 871.9006) 
(list 5120.135 871.9108) 
(list 5120.135 871.9211) 
(list 5120.135 871.9314) 
(list 5120.135 871.9417) 
(list 5120.135 871.9519) 
(list 5120.135 871.9622) 
(list 5120.135 871.9725) 
(list 5120.135 871.9828) 
(list 5120.135 871.9931) 
(list 5120.135 872.0033) 
(list 5120.135 872.0136) 
(list 5120.135 872.0239) 
(list 5120.135 872.0342) 
(list 5120.135 872.0444) 
(list 5120.135 872.0547) 
(list 5120.135 872.065) 
(list 5120.135 872.0753) 
(list 5120.135 872.0856) 
(list 5120.135 872.0958) 
(list 5120.135 872.1061) 
(list 5120.135 872.1164) 
(list 5120.135 872.1267) 
(list 5120.135 872.1369) 
(list 5120.135 872.1472) 
(list 5120.135 872.1575) 
(list 5120.135 872.1678) 
(list 5120.135 872.1781) 
(list 5120.135 872.1883) 
(list 5120.135 872.1986) 
(list 5120.135 872.2089) 
(list 5120.135 872.2192) 
(list 5120.135 872.2294) 
(list 5120.135 872.2397) 
(list 5120.135 872.25) 
(list 5120 872.25)))
(apply 'command (append '("pline") coords '("c")))
(setq tap16 (ssadd (entlast) tap16))
(command "_mirror" (entlast) "" "5120,900" "5120,901" "No")
(setq tap16 (ssadd (entlast) tap16))
(setq coords (list 
(list 5120.563 871.88) 
(list 5120.5531 871.88) 
(list 5120.5515 871.8903) 
(list 5120.5459 871.9006) 
(list 5120.5367 871.9108) 
(list 5120.5241 871.9211) 
(list 5120.5084 871.9314) 
(list 5120.4901 871.9417) 
(list 5120.4697 871.9519) 
(list 5120.448 871.9622) 
(list 5120.4254 871.9725) 
(list 5120.4028 871.9828) 
(list 5120.3808 871.9931) 
(list 5120.3601 872.0033) 
(list 5120.3412 872.0136) 
(list 5120.3249 872.0239) 
(list 5120.3115 872.0342) 
(list 5120.3016 872.0444) 
(list 5120.2954 872.0547) 
(list 5120.2932 872.065) 
(list 5120.295 872.0753) 
(list 5120.3008 872.0856) 
(list 5120.3103 872.0958) 
(list 5120.3235 872.1061) 
(list 5120.3398 872.1164) 
(list 5120.3588 872.1267) 
(list 5120.3799 872.1369) 
(list 5120.4024 872.1472) 
(list 5120.4258 872.1575) 
(list 5120.4493 872.1678) 
(list 5120.4721 872.1781) 
(list 5120.4936 872.1883) 
(list 5120.5131 872.1986) 
(list 5120.5301 872.2089) 
(list 5120.5439 872.2192) 
(list 5120.5542 872.2294) 
(list 5120.5606 872.2397) 
(list 5120.563 872.25) 
(list 5120.563 872.25)))
(apply 'command (append '("pline") coords '("c")))
(setq tap16 (ssadd (entlast) tap16))
(command "_mirror" (entlast) "" "5120,900" "5120,901" "No")
(setq tap16 (ssadd (entlast) tap16))
(setq coords (list 
(list 5121.126 871.88) 
(list 5120.563 871.88) 
(list 5120.563 871.8903) 
(list 5120.563 871.9006) 
(list 5120.563 871.9108) 
(list 5120.563 871.9211) 
(list 5120.563 871.9314) 
(list 5120.563 871.9417) 
(list 5120.563 871.9519) 
(list 5120.563 871.9622) 
(list 5120.563 871.9725) 
(list 5120.563 871.9828) 
(list 5120.563 871.9931) 
(list 5120.563 872.0033) 
(list 5120.563 872.0136) 
(list 5120.563 872.0239) 
(list 5120.563 872.0342) 
(list 5120.563 872.0444) 
(list 5120.563 872.0547) 
(list 5120.563 872.065) 
(list 5120.563 872.0753) 
(list 5120.563 872.0856) 
(list 5120.563 872.0958) 
(list 5120.563 872.1061) 
(list 5120.563 872.1164) 
(list 5120.563 872.1267) 
(list 5120.563 872.1369) 
(list 5120.563 872.1472) 
(list 5120.563 872.1575) 
(list 5120.563 872.1678) 
(list 5120.563 872.1781) 
(list 5120.563 872.1883) 
(list 5120.563 872.1986) 
(list 5120.563 872.2089) 
(list 5120.563 872.2192) 
(list 5120.563 872.2294) 
(list 5120.563 872.2397) 
(list 5120.563 872.25) 
(list 5121.126 872.25)))
(apply 'command (append '("pline") coords '("c")))
(setq tap16 (ssadd (entlast) tap16))
(command "_mirror" (entlast) "" "5120,900" "5120,901" "No")
(setq tap16 (ssadd (entlast) tap16))
(command "_block" "blktap16" "5120,900" tap16 "")
(command "_insert" "blktap16" "5120,900" "1" "1" "0")
(command "_insert" "blktap16" "5120,900" "1" "1" "180")
(setq uc16 nil)
(setq uc16 (ssadd))
(setq coords (list 
(list 0 -0.185) 
(list 0.135 -0.185) 
(list 0.135 -0.17472) 
(list 0.135 -0.16444) 
(list 0.135 -0.15417) 
(list 0.135 -0.14389) 
(list 0.135 -0.13361) 
(list 0.135 -0.12333) 
(list 0.135 -0.11306) 
(list 0.135 -0.10278) 
(list 0.135 -0.0925) 
(list 0.135 -0.082222) 
(list 0.135 -0.071944) 
(list 0.135 -0.061667) 
(list 0.135 -0.051389) 
(list 0.135 -0.041111) 
(list 0.135 -0.030833) 
(list 0.135 -0.020556) 
(list 0.135 -0.010278) 
(list 0.135 0) 
(list 0.135 0.010278) 
(list 0.135 0.020556) 
(list 0.135 0.030833) 
(list 0.135 0.041111) 
(list 0.135 0.051389) 
(list 0.135 0.061667) 
(list 0.135 0.071944) 
(list 0.135 0.082222) 
(list 0.135 0.0925) 
(list 0.135 0.10278) 
(list 0.135 0.11306) 
(list 0.135 0.12333) 
(list 0.135 0.13361) 
(list 0.135 0.14389) 
(list 0.135 0.15417) 
(list 0.135 0.16444) 
(list 0.135 0.17472) 
(list 0.135 0.185) 
(list 0 0.185)))
(apply 'command (append '("pline") coords '("c")))
(setq uc16 (ssadd (entlast) uc16))
(setq coords (list 
(list 1.126 -0.185) 
(list 0.563 -0.185) 
(list 0.56092 -0.17472) 
(list 0.55474 -0.16444) 
(list 0.54465 -0.15417) 
(list 0.53095 -0.14389) 
(list 0.51406 -0.13361) 
(list 0.4945 -0.12333) 
(list 0.47286 -0.11306) 
(list 0.44979 -0.10278) 
(list 0.426 -0.0925) 
(list 0.40221 -0.082222) 
(list 0.37914 -0.071944) 
(list 0.3575 -0.061667) 
(list 0.33794 -0.051389) 
(list 0.32105 -0.041111) 
(list 0.30735 -0.030833) 
(list 0.29726 -0.020556) 
(list 0.29108 -0.010278) 
(list 0.289 0) 
(list 0.29108 0.010278) 
(list 0.29726 0.020556) 
(list 0.30735 0.030833) 
(list 0.32105 0.041111) 
(list 0.33794 0.051389) 
(list 0.3575 0.061667) 
(list 0.37914 0.071944) 
(list 0.40221 0.082222) 
(list 0.426 0.0925) 
(list 0.44979 0.10278) 
(list 0.47286 0.11306) 
(list 0.4945 0.12333) 
(list 0.51406 0.13361) 
(list 0.53095 0.14389) 
(list 0.54465 0.15417) 
(list 0.55474 0.16444) 
(list 0.56092 0.17472) 
(list 0.563 0.185) 
(list 1.126 0.185)))
(apply 'command (append '("pline") coords '("c")))
(setq uc16 (ssadd (entlast) uc16))
(command "_block" "blkuc16" "0,0.185" uc16 "")
(command "_insert" "blkuc16" "5120,872.62" "1" "1" "0")
(command "_insert" "blkuc16" "5120,872.25" "1" "1" "180")
(command "_insert" "blkuc16" "5120,872.99" "1" "1" "0")
(command "_insert" "blkuc16" "5120,872.62" "1" "1" "180")
(command "_insert" "blkuc16" "5120,873.36" "1" "1" "0")
(command "_insert" "blkuc16" "5120,872.99" "1" "1" "180")
(command "_insert" "blkuc16" "5120,873.73" "1" "1" "0")
(command "_insert" "blkuc16" "5120,873.36" "1" "1" "180")
(command "_insert" "blkuc16" "5120,874.1" "1" "1" "0")
(command "_insert" "blkuc16" "5120,873.73" "1" "1" "180")
(command "_insert" "blkuc16" "5120,874.47" "1" "1" "0")
(command "_insert" "blkuc16" "5120,874.1" "1" "1" "180")
(command "_insert" "blkuc16" "5120,874.84" "1" "1" "0")
(command "_insert" "blkuc16" "5120,874.47" "1" "1" "180")
(command "_insert" "blkuc16" "5120,875.21" "1" "1" "0")
(command "_insert" "blkuc16" "5120,874.84" "1" "1" "180")
(command "_insert" "blkuc16" "5120,875.58" "1" "1" "0")
(command "_insert" "blkuc16" "5120,875.21" "1" "1" "180")
(command "_insert" "blkuc16" "5120,875.95" "1" "1" "0")
(command "_insert" "blkuc16" "5120,875.58" "1" "1" "180")
(command "_insert" "blkuc16" "5120,876.32" "1" "1" "0")
(command "_insert" "blkuc16" "5120,875.95" "1" "1" "180")
(command "_insert" "blkuc16" "5120,876.69" "1" "1" "0")
(command "_insert" "blkuc16" "5120,876.32" "1" "1" "180")
(command "_insert" "blkuc16" "5120,877.06" "1" "1" "0")
(command "_insert" "blkuc16" "5120,876.69" "1" "1" "180")
(command "_insert" "blkuc16" "5120,877.43" "1" "1" "0")
(command "_insert" "blkuc16" "5120,877.06" "1" "1" "180")
(command "_insert" "blkuc16" "5120,877.8" "1" "1" "0")
(command "_insert" "blkuc16" "5120,877.43" "1" "1" "180")
(command "_insert" "blkuc16" "5120,878.17" "1" "1" "0")
(command "_insert" "blkuc16" "5120,877.8" "1" "1" "180")
(command "_insert" "blkuc16" "5120,878.54" "1" "1" "0")
(command "_insert" "blkuc16" "5120,878.17" "1" "1" "180")
(command "_insert" "blkuc16" "5120,878.91" "1" "1" "0")
(command "_insert" "blkuc16" "5120,878.54" "1" "1" "180")
(command "_insert" "blkuc16" "5120,879.28" "1" "1" "0")
(command "_insert" "blkuc16" "5120,878.91" "1" "1" "180")
(command "_insert" "blkuc16" "5120,879.65" "1" "1" "0")
(command "_insert" "blkuc16" "5120,879.28" "1" "1" "180")
(command "_insert" "blkuc16" "5120,880.02" "1" "1" "0")
(command "_insert" "blkuc16" "5120,879.65" "1" "1" "180")
(command "_insert" "blkuc16" "5120,880.39" "1" "1" "0")
(command "_insert" "blkuc16" "5120,880.02" "1" "1" "180")
(command "_insert" "blkuc16" "5120,880.76" "1" "1" "0")
(command "_insert" "blkuc16" "5120,880.39" "1" "1" "180")
(command "_insert" "blkuc16" "5120,881.13" "1" "1" "0")
(command "_insert" "blkuc16" "5120,880.76" "1" "1" "180")
(command "_insert" "blkuc16" "5120,881.5" "1" "1" "0")
(command "_insert" "blkuc16" "5120,881.13" "1" "1" "180")
(command "_insert" "blkuc16" "5120,881.87" "1" "1" "0")
(command "_insert" "blkuc16" "5120,881.5" "1" "1" "180")
(command "_insert" "blkuc16" "5120,882.24" "1" "1" "0")
(command "_insert" "blkuc16" "5120,881.87" "1" "1" "180")
(command "_insert" "blkuc16" "5120,882.61" "1" "1" "0")
(command "_insert" "blkuc16" "5120,882.24" "1" "1" "180")
(command "_insert" "blkuc16" "5120,882.98" "1" "1" "0")
(command "_insert" "blkuc16" "5120,882.61" "1" "1" "180")
(command "_insert" "blkuc16" "5120,883.35" "1" "1" "0")
(command "_insert" "blkuc16" "5120,882.98" "1" "1" "180")
(command "_insert" "blkuc16" "5120,883.72" "1" "1" "0")
(command "_insert" "blkuc16" "5120,883.35" "1" "1" "180")
(command "_insert" "blkuc16" "5120,884.09" "1" "1" "0")
(command "_insert" "blkuc16" "5120,883.72" "1" "1" "180")
(command "_insert" "blkuc16" "5120,884.46" "1" "1" "0")
(command "_insert" "blkuc16" "5120,884.09" "1" "1" "180")
(command "_insert" "blkuc16" "5120,884.83" "1" "1" "0")
(command "_insert" "blkuc16" "5120,884.46" "1" "1" "180")
(command "_insert" "blkuc16" "5120,885.2" "1" "1" "0")
(command "_insert" "blkuc16" "5120,884.83" "1" "1" "180")
(command "_insert" "blkuc16" "5120,885.57" "1" "1" "0")
(command "_insert" "blkuc16" "5120,885.2" "1" "1" "180")
(command "_insert" "blkuc16" "5120,885.94" "1" "1" "0")
(command "_insert" "blkuc16" "5120,885.57" "1" "1" "180")
(command "_insert" "blkuc16" "5120,886.31" "1" "1" "0")
(command "_insert" "blkuc16" "5120,885.94" "1" "1" "180")
(command "_insert" "blkuc16" "5120,886.68" "1" "1" "0")
(command "_insert" "blkuc16" "5120,886.31" "1" "1" "180")
(command "_insert" "blkuc16" "5120,887.05" "1" "1" "0")
(command "_insert" "blkuc16" "5120,886.68" "1" "1" "180")
(command "_insert" "blkuc16" "5120,887.42" "1" "1" "0")
(command "_insert" "blkuc16" "5120,887.05" "1" "1" "180")
(command "_insert" "blkuc16" "5120,887.79" "1" "1" "0")
(command "_insert" "blkuc16" "5120,887.42" "1" "1" "180")
(command "_insert" "blkuc16" "5120,888.16" "1" "1" "0")
(command "_insert" "blkuc16" "5120,887.79" "1" "1" "180")
(command "_insert" "blkuc16" "5120,888.53" "1" "1" "0")
(command "_insert" "blkuc16" "5120,888.16" "1" "1" "180")
(command "_insert" "blkuc16" "5120,888.9" "1" "1" "0")
(command "_insert" "blkuc16" "5120,888.53" "1" "1" "180")
(command "_insert" "blkuc16" "5120,889.27" "1" "1" "0")
(command "_insert" "blkuc16" "5120,888.9" "1" "1" "180")
(command "_insert" "blkuc16" "5120,889.64" "1" "1" "0")
(command "_insert" "blkuc16" "5120,889.27" "1" "1" "180")
(command "_insert" "blkuc16" "5120,890.01" "1" "1" "0")
(command "_insert" "blkuc16" "5120,889.64" "1" "1" "180")
(command "_insert" "blkuc16" "5120,890.38" "1" "1" "0")
(command "_insert" "blkuc16" "5120,890.01" "1" "1" "180")
(command "_insert" "blkuc16" "5120,890.75" "1" "1" "0")
(command "_insert" "blkuc16" "5120,890.38" "1" "1" "180")
(command "_insert" "blkuc16" "5120,891.12" "1" "1" "0")
(command "_insert" "blkuc16" "5120,890.75" "1" "1" "180")
(command "_insert" "blkuc16" "5120,891.49" "1" "1" "0")
(command "_insert" "blkuc16" "5120,891.12" "1" "1" "180")
(command "_insert" "blkuc16" "5120,891.86" "1" "1" "0")
(command "_insert" "blkuc16" "5120,891.49" "1" "1" "180")
(command "_insert" "blkuc16" "5120,892.23" "1" "1" "0")
(command "_insert" "blkuc16" "5120,891.86" "1" "1" "180")
(command "_insert" "blkuc16" "5120,892.6" "1" "1" "0")
(command "_insert" "blkuc16" "5120,892.23" "1" "1" "180")
(command "_insert" "blkuc16" "5120,892.97" "1" "1" "0")
(command "_insert" "blkuc16" "5120,892.6" "1" "1" "180")
(command "_insert" "blkuc16" "5120,893.34" "1" "1" "0")
(command "_insert" "blkuc16" "5120,892.97" "1" "1" "180")
(command "_insert" "blkuc16" "5120,893.71" "1" "1" "0")
(command "_insert" "blkuc16" "5120,893.34" "1" "1" "180")
(command "_insert" "blkuc16" "5120,894.08" "1" "1" "0")
(command "_insert" "blkuc16" "5120,893.71" "1" "1" "180")
(command "_insert" "blkuc16" "5120,894.45" "1" "1" "0")
(command "_insert" "blkuc16" "5120,894.08" "1" "1" "180")
(command "_insert" "blkuc16" "5120,894.82" "1" "1" "0")
(command "_insert" "blkuc16" "5120,894.45" "1" "1" "180")
(command "_insert" "blkuc16" "5120,895.19" "1" "1" "0")
(command "_insert" "blkuc16" "5120,894.82" "1" "1" "180")
(command "_insert" "blkuc16" "5120,895.56" "1" "1" "0")
(command "_insert" "blkuc16" "5120,895.19" "1" "1" "180")
(command "_insert" "blkuc16" "5120,895.93" "1" "1" "0")
(command "_insert" "blkuc16" "5120,895.56" "1" "1" "180")
(command "_insert" "blkuc16" "5120,896.3" "1" "1" "0")
(command "_insert" "blkuc16" "5120,895.93" "1" "1" "180")
(command "_insert" "blkuc16" "5120,896.67" "1" "1" "0")
(command "_insert" "blkuc16" "5120,896.3" "1" "1" "180")
(command "_insert" "blkuc16" "5120,897.04" "1" "1" "0")
(command "_insert" "blkuc16" "5120,896.67" "1" "1" "180")
(command "_insert" "blkuc16" "5120,897.41" "1" "1" "0")
(command "_insert" "blkuc16" "5120,897.04" "1" "1" "180")
(command "_insert" "blkuc16" "5120,897.78" "1" "1" "0")
(command "_insert" "blkuc16" "5120,897.41" "1" "1" "180")
(command "_insert" "blkuc16" "5120,898.15" "1" "1" "0")
(command "_insert" "blkuc16" "5120,897.78" "1" "1" "180")
(command "_insert" "blkuc16" "5120,898.52" "1" "1" "0")
(command "_insert" "blkuc16" "5120,898.15" "1" "1" "180")
(command "_insert" "blkuc16" "5120,898.89" "1" "1" "0")
(command "_insert" "blkuc16" "5120,898.52" "1" "1" "180")
(command "_insert" "blkuc16" "5120,899.26" "1" "1" "0")
(command "_insert" "blkuc16" "5120,898.89" "1" "1" "180")
(command "_insert" "blkuc16" "5120,899.63" "1" "1" "0")
(command "_insert" "blkuc16" "5120,899.26" "1" "1" "180")
(command "_insert" "blkuc16" "5120,900" "1" "1" "0")
(command "_insert" "blkuc16" "5120,899.63" "1" "1" "180")
(command "_insert" "blkuc16" "5120,900.37" "1" "1" "0")
(command "_insert" "blkuc16" "5120,900" "1" "1" "180")
(command "_insert" "blkuc16" "5120,900.74" "1" "1" "0")
(command "_insert" "blkuc16" "5120,900.37" "1" "1" "180")
(command "_insert" "blkuc16" "5120,901.11" "1" "1" "0")
(command "_insert" "blkuc16" "5120,900.74" "1" "1" "180")
(command "_insert" "blkuc16" "5120,901.48" "1" "1" "0")
(command "_insert" "blkuc16" "5120,901.11" "1" "1" "180")
(command "_insert" "blkuc16" "5120,901.85" "1" "1" "0")
(command "_insert" "blkuc16" "5120,901.48" "1" "1" "180")
(command "_insert" "blkuc16" "5120,902.22" "1" "1" "0")
(command "_insert" "blkuc16" "5120,901.85" "1" "1" "180")
(command "_insert" "blkuc16" "5120,902.59" "1" "1" "0")
(command "_insert" "blkuc16" "5120,902.22" "1" "1" "180")
(command "_insert" "blkuc16" "5120,902.96" "1" "1" "0")
(command "_insert" "blkuc16" "5120,902.59" "1" "1" "180")
(command "_insert" "blkuc16" "5120,903.33" "1" "1" "0")
(command "_insert" "blkuc16" "5120,902.96" "1" "1" "180")
(command "_insert" "blkuc16" "5120,903.7" "1" "1" "0")
(command "_insert" "blkuc16" "5120,903.33" "1" "1" "180")
(command "_insert" "blkuc16" "5120,904.07" "1" "1" "0")
(command "_insert" "blkuc16" "5120,903.7" "1" "1" "180")
(command "_insert" "blkuc16" "5120,904.44" "1" "1" "0")
(command "_insert" "blkuc16" "5120,904.07" "1" "1" "180")
(command "_insert" "blkuc16" "5120,904.81" "1" "1" "0")
(command "_insert" "blkuc16" "5120,904.44" "1" "1" "180")
(command "_insert" "blkuc16" "5120,905.18" "1" "1" "0")
(command "_insert" "blkuc16" "5120,904.81" "1" "1" "180")
(command "_insert" "blkuc16" "5120,905.55" "1" "1" "0")
(command "_insert" "blkuc16" "5120,905.18" "1" "1" "180")
(command "_insert" "blkuc16" "5120,905.92" "1" "1" "0")
(command "_insert" "blkuc16" "5120,905.55" "1" "1" "180")
(command "_insert" "blkuc16" "5120,906.29" "1" "1" "0")
(command "_insert" "blkuc16" "5120,905.92" "1" "1" "180")
(command "_insert" "blkuc16" "5120,906.66" "1" "1" "0")
(command "_insert" "blkuc16" "5120,906.29" "1" "1" "180")
(command "_insert" "blkuc16" "5120,907.03" "1" "1" "0")
(command "_insert" "blkuc16" "5120,906.66" "1" "1" "180")
(command "_insert" "blkuc16" "5120,907.4" "1" "1" "0")
(command "_insert" "blkuc16" "5120,907.03" "1" "1" "180")
(command "_insert" "blkuc16" "5120,907.77" "1" "1" "0")
(command "_insert" "blkuc16" "5120,907.4" "1" "1" "180")
(command "_insert" "blkuc16" "5120,908.14" "1" "1" "0")
(command "_insert" "blkuc16" "5120,907.77" "1" "1" "180")
(command "_insert" "blkuc16" "5120,908.51" "1" "1" "0")
(command "_insert" "blkuc16" "5120,908.14" "1" "1" "180")
(command "_insert" "blkuc16" "5120,908.88" "1" "1" "0")
(command "_insert" "blkuc16" "5120,908.51" "1" "1" "180")
(command "_insert" "blkuc16" "5120,909.25" "1" "1" "0")
(command "_insert" "blkuc16" "5120,908.88" "1" "1" "180")
(command "_insert" "blkuc16" "5120,909.62" "1" "1" "0")
(command "_insert" "blkuc16" "5120,909.25" "1" "1" "180")
(command "_insert" "blkuc16" "5120,909.99" "1" "1" "0")
(command "_insert" "blkuc16" "5120,909.62" "1" "1" "180")
(command "_insert" "blkuc16" "5120,910.36" "1" "1" "0")
(command "_insert" "blkuc16" "5120,909.99" "1" "1" "180")
(command "_insert" "blkuc16" "5120,910.73" "1" "1" "0")
(command "_insert" "blkuc16" "5120,910.36" "1" "1" "180")
(command "_insert" "blkuc16" "5120,911.1" "1" "1" "0")
(command "_insert" "blkuc16" "5120,910.73" "1" "1" "180")
(command "_insert" "blkuc16" "5120,911.47" "1" "1" "0")
(command "_insert" "blkuc16" "5120,911.1" "1" "1" "180")
(command "_insert" "blkuc16" "5120,911.84" "1" "1" "0")
(command "_insert" "blkuc16" "5120,911.47" "1" "1" "180")
(command "_insert" "blkuc16" "5120,912.21" "1" "1" "0")
(command "_insert" "blkuc16" "5120,911.84" "1" "1" "180")
(command "_insert" "blkuc16" "5120,912.58" "1" "1" "0")
(command "_insert" "blkuc16" "5120,912.21" "1" "1" "180")
(command "_insert" "blkuc16" "5120,912.95" "1" "1" "0")
(command "_insert" "blkuc16" "5120,912.58" "1" "1" "180")
(command "_insert" "blkuc16" "5120,913.32" "1" "1" "0")
(command "_insert" "blkuc16" "5120,912.95" "1" "1" "180")
(command "_insert" "blkuc16" "5120,913.69" "1" "1" "0")
(command "_insert" "blkuc16" "5120,913.32" "1" "1" "180")
(command "_insert" "blkuc16" "5120,914.06" "1" "1" "0")
(command "_insert" "blkuc16" "5120,913.69" "1" "1" "180")
(command "_insert" "blkuc16" "5120,914.43" "1" "1" "0")
(command "_insert" "blkuc16" "5120,914.06" "1" "1" "180")
(command "_insert" "blkuc16" "5120,914.8" "1" "1" "0")
(command "_insert" "blkuc16" "5120,914.43" "1" "1" "180")
(command "_insert" "blkuc16" "5120,915.17" "1" "1" "0")
(command "_insert" "blkuc16" "5120,914.8" "1" "1" "180")
(command "_insert" "blkuc16" "5120,915.54" "1" "1" "0")
(command "_insert" "blkuc16" "5120,915.17" "1" "1" "180")
(command "_insert" "blkuc16" "5120,915.91" "1" "1" "0")
(command "_insert" "blkuc16" "5120,915.54" "1" "1" "180")
(command "_insert" "blkuc16" "5120,916.28" "1" "1" "0")
(command "_insert" "blkuc16" "5120,915.91" "1" "1" "180")
(command "_insert" "blkuc16" "5120,916.65" "1" "1" "0")
(command "_insert" "blkuc16" "5120,916.28" "1" "1" "180")
(command "_insert" "blkuc16" "5120,917.02" "1" "1" "0")
(command "_insert" "blkuc16" "5120,916.65" "1" "1" "180")
(command "_insert" "blkuc16" "5120,917.39" "1" "1" "0")
(command "_insert" "blkuc16" "5120,917.02" "1" "1" "180")
(command "_insert" "blkuc16" "5120,917.76" "1" "1" "0")
(command "_insert" "blkuc16" "5120,917.39" "1" "1" "180")
(command "_insert" "blkuc16" "5120,918.13" "1" "1" "0")
(command "_insert" "blkuc16" "5120,917.76" "1" "1" "180")
(command "_insert" "blkuc16" "5120,918.5" "1" "1" "0")
(command "_insert" "blkuc16" "5120,918.13" "1" "1" "180")
(command "_insert" "blkuc16" "5120,918.87" "1" "1" "0")
(command "_insert" "blkuc16" "5120,918.5" "1" "1" "180")
(command "_insert" "blkuc16" "5120,919.24" "1" "1" "0")
(command "_insert" "blkuc16" "5120,918.87" "1" "1" "180")
(command "_insert" "blkuc16" "5120,919.61" "1" "1" "0")
(command "_insert" "blkuc16" "5120,919.24" "1" "1" "180")
(command "_insert" "blkuc16" "5120,919.98" "1" "1" "0")
(command "_insert" "blkuc16" "5120,919.61" "1" "1" "180")
(command "_insert" "blkuc16" "5120,920.35" "1" "1" "0")
(command "_insert" "blkuc16" "5120,919.98" "1" "1" "180")
(command "_insert" "blkuc16" "5120,920.72" "1" "1" "0")
(command "_insert" "blkuc16" "5120,920.35" "1" "1" "180")
(command "_insert" "blkuc16" "5120,921.09" "1" "1" "0")
(command "_insert" "blkuc16" "5120,920.72" "1" "1" "180")
(command "_insert" "blkuc16" "5120,921.46" "1" "1" "0")
(command "_insert" "blkuc16" "5120,921.09" "1" "1" "180")
(command "_insert" "blkuc16" "5120,921.83" "1" "1" "0")
(command "_insert" "blkuc16" "5120,921.46" "1" "1" "180")
(command "_insert" "blkuc16" "5120,922.2" "1" "1" "0")
(command "_insert" "blkuc16" "5120,921.83" "1" "1" "180")
(command "_insert" "blkuc16" "5120,922.57" "1" "1" "0")
(command "_insert" "blkuc16" "5120,922.2" "1" "1" "180")
(command "_insert" "blkuc16" "5120,922.94" "1" "1" "0")
(command "_insert" "blkuc16" "5120,922.57" "1" "1" "180")
(command "_insert" "blkuc16" "5120,923.31" "1" "1" "0")
(command "_insert" "blkuc16" "5120,922.94" "1" "1" "180")
(command "_insert" "blkuc16" "5120,923.68" "1" "1" "0")
(command "_insert" "blkuc16" "5120,923.31" "1" "1" "180")
(command "_insert" "blkuc16" "5120,924.05" "1" "1" "0")
(command "_insert" "blkuc16" "5120,923.68" "1" "1" "180")
(command "_insert" "blkuc16" "5120,924.42" "1" "1" "0")
(command "_insert" "blkuc16" "5120,924.05" "1" "1" "180")
(command "_insert" "blkuc16" "5120,924.79" "1" "1" "0")
(command "_insert" "blkuc16" "5120,924.42" "1" "1" "180")
(command "_insert" "blkuc16" "5120,925.16" "1" "1" "0")
(command "_insert" "blkuc16" "5120,924.79" "1" "1" "180")
(command "_insert" "blkuc16" "5120,925.53" "1" "1" "0")
(command "_insert" "blkuc16" "5120,925.16" "1" "1" "180")
(command "_insert" "blkuc16" "5120,925.9" "1" "1" "0")
(command "_insert" "blkuc16" "5120,925.53" "1" "1" "180")
(command "_insert" "blkuc16" "5120,926.27" "1" "1" "0")
(command "_insert" "blkuc16" "5120,925.9" "1" "1" "180")
(command "_insert" "blkuc16" "5120,926.64" "1" "1" "0")
(command "_insert" "blkuc16" "5120,926.27" "1" "1" "180")
(command "_insert" "blkuc16" "5120,927.01" "1" "1" "0")
(command "_insert" "blkuc16" "5120,926.64" "1" "1" "180")
(command "_insert" "blkuc16" "5120,927.38" "1" "1" "0")
(command "_insert" "blkuc16" "5120,927.01" "1" "1" "180")
(command "_insert" "blkuc16" "5120,927.75" "1" "1" "0")
(command "_insert" "blkuc16" "5120,927.38" "1" "1" "180")
(command "_layer" "set" "phccover" "")
(command "_rectangle" "5118.874,933.3" "5121.126,866.7")
(command "_layer" "set" "nitride" "")
(setq phc16 currobj)
(command "_layer" "set" "cover" "")
(command "_rectangle" "5118.874,836.7" "5121.126,963.3")
(command "_layer" "set" "nitride" "")
(command "_layer" "set" "text" "")
(command "_circle" "5117.924,846.7" "0.075")
(command "_circle" "5117.549,846.7" "0.15")
(command "_circle" "5117.174,846.7" "0.075")
(command "_circle" "5116.799,846.7" "0.15")
(command "_circle" "5117.924,848.7" "0.075")
(command "_circle" "5117.549,848.7" "0.075")
(command "_circle" "5117.174,848.7" "0.15")
(command "_circle" "5116.799,848.7" "0.15")
(command "_circle" "5117.924,850.7" "0.075")
(command "_circle" "5117.549,850.7" "0.15")
(command "_circle" "5117.174,850.7" "0.15")
(command "_circle" "5116.799,850.7" "0.15")
(command "_circle" "5117.924,852.7" "0.075")
(command "_circle" "5117.549,852.7" "0.075")
(command "_circle" "5117.174,852.7" "0.075")
(command "_circle" "5116.799,852.7" "0.075")
(command "_circle" "5116.424,852.7" "0.15")
(command "_circle" "5117.924,854.7" "0.075")
(command "_circle" "5117.549,854.7" "0.15")
(command "_circle" "5117.174,854.7" "0.075")
(command "_circle" "5116.799,854.7" "0.075")
(command "_circle" "5116.424,854.7" "0.15")
(command "_circle" "5117.924,856.7" "0.075")
(command "_circle" "5117.549,856.7" "0.075")
(command "_circle" "5117.174,856.7" "0.15")
(command "_circle" "5116.799,856.7" "0.075")
(command "_circle" "5116.424,856.7" "0.15")
(command "_circle" "5117.924,858.7" "0.075")
(command "_circle" "5117.549,858.7" "0.15")
(command "_circle" "5117.174,858.7" "0.15")
(command "_circle" "5116.799,858.7" "0.075")
(command "_circle" "5116.424,858.7" "0.15")
(command "_circle" "5117.924,860.7" "0.075")
(command "_circle" "5117.549,860.7" "0.075")
(command "_circle" "5117.174,860.7" "0.075")
(command "_circle" "5116.799,860.7" "0.15")
(command "_circle" "5116.424,860.7" "0.15")
(command "_circle" "5117.924,862.7" "0.075")
(command "_circle" "5117.549,862.7" "0.15")
(command "_circle" "5117.174,862.7" "0.075")
(command "_circle" "5116.799,862.7" "0.15")
(command "_circle" "5116.424,862.7" "0.15")
(command "_circle" "5117.924,864.7" "0.075")
(command "_circle" "5117.549,864.7" "0.075")
(command "_circle" "5117.174,864.7" "0.15")
(command "_circle" "5116.799,864.7" "0.15")
(command "_circle" "5116.424,864.7" "0.15")
(command "_circle" "5117.924,866.7" "0.075")
(command "_circle" "5117.549,866.7" "0.15")
(command "_circle" "5117.174,866.7" "0.15")
(command "_circle" "5116.799,866.7" "0.15")
(command "_circle" "5116.424,866.7" "0.15")
(command "_circle" "5117.924,868.7" "0.075")
(command "_circle" "5117.549,868.7" "0.075")
(command "_circle" "5117.174,868.7" "0.075")
(command "_circle" "5116.799,868.7" "0.075")
(command "_circle" "5116.424,868.7" "0.075")
(command "_circle" "5116.049,868.7" "0.15")
(command "_circle" "5117.924,870.7" "0.075")
(command "_circle" "5117.549,870.7" "0.15")
(command "_circle" "5117.174,870.7" "0.075")
(command "_circle" "5116.799,870.7" "0.075")
(command "_circle" "5116.424,870.7" "0.075")
(command "_circle" "5116.049,870.7" "0.15")
(command "_circle" "5117.924,872.7" "0.075")
(command "_circle" "5117.549,872.7" "0.075")
(command "_circle" "5117.174,872.7" "0.15")
(command "_circle" "5116.799,872.7" "0.075")
(command "_circle" "5116.424,872.7" "0.075")
(command "_circle" "5116.049,872.7" "0.15")
(command "_circle" "5117.924,874.7" "0.075")
(command "_circle" "5117.549,874.7" "0.15")
(command "_circle" "5117.174,874.7" "0.15")
(command "_circle" "5116.799,874.7" "0.075")
(command "_circle" "5116.424,874.7" "0.075")
(command "_circle" "5116.049,874.7" "0.15")
(command "_circle" "5117.924,876.7" "0.075")
(command "_circle" "5117.549,876.7" "0.075")
(command "_circle" "5117.174,876.7" "0.075")
(command "_circle" "5116.799,876.7" "0.15")
(command "_circle" "5116.424,876.7" "0.075")
(command "_circle" "5116.049,876.7" "0.15")
(command "_circle" "5117.924,878.7" "0.075")
(command "_circle" "5117.549,878.7" "0.15")
(command "_circle" "5117.174,878.7" "0.075")
(command "_circle" "5116.799,878.7" "0.15")
(command "_circle" "5116.424,878.7" "0.075")
(command "_circle" "5116.049,878.7" "0.15")
(command "_circle" "5117.924,880.7" "0.075")
(command "_circle" "5117.549,880.7" "0.075")
(command "_circle" "5117.174,880.7" "0.15")
(command "_circle" "5116.799,880.7" "0.15")
(command "_circle" "5116.424,880.7" "0.075")
(command "_circle" "5116.049,880.7" "0.15")
(command "_circle" "5117.924,882.7" "0.075")
(command "_circle" "5117.549,882.7" "0.15")
(command "_circle" "5117.174,882.7" "0.15")
(command "_circle" "5116.799,882.7" "0.15")
(command "_circle" "5116.424,882.7" "0.075")
(command "_circle" "5116.049,882.7" "0.15")
(command "_circle" "5117.924,884.7" "0.075")
(command "_circle" "5117.549,884.7" "0.075")
(command "_circle" "5117.174,884.7" "0.075")
(command "_circle" "5116.799,884.7" "0.075")
(command "_circle" "5116.424,884.7" "0.15")
(command "_circle" "5116.049,884.7" "0.15")
(command "_circle" "5117.924,886.7" "0.075")
(command "_circle" "5117.549,886.7" "0.15")
(command "_circle" "5117.174,886.7" "0.075")
(command "_circle" "5116.799,886.7" "0.075")
(command "_circle" "5116.424,886.7" "0.15")
(command "_circle" "5116.049,886.7" "0.15")
(command "_circle" "5117.924,888.7" "0.075")
(command "_circle" "5117.549,888.7" "0.075")
(command "_circle" "5117.174,888.7" "0.15")
(command "_circle" "5116.799,888.7" "0.075")
(command "_circle" "5116.424,888.7" "0.15")
(command "_circle" "5116.049,888.7" "0.15")
(command "_circle" "5117.924,890.7" "0.075")
(command "_circle" "5117.549,890.7" "0.15")
(command "_circle" "5117.174,890.7" "0.15")
(command "_circle" "5116.799,890.7" "0.075")
(command "_circle" "5116.424,890.7" "0.15")
(command "_circle" "5116.049,890.7" "0.15")
(command "_circle" "5117.924,892.7" "0.075")
(command "_circle" "5117.549,892.7" "0.075")
(command "_circle" "5117.174,892.7" "0.075")
(command "_circle" "5116.799,892.7" "0.15")
(command "_circle" "5116.424,892.7" "0.15")
(command "_circle" "5116.049,892.7" "0.15")
(command "_circle" "5117.924,894.7" "0.075")
(command "_circle" "5117.549,894.7" "0.15")
(command "_circle" "5117.174,894.7" "0.075")
(command "_circle" "5116.799,894.7" "0.15")
(command "_circle" "5116.424,894.7" "0.15")
(command "_circle" "5116.049,894.7" "0.15")
(command "_circle" "5117.924,896.7" "0.075")
(command "_circle" "5117.549,896.7" "0.075")
(command "_circle" "5117.174,896.7" "0.15")
(command "_circle" "5116.799,896.7" "0.15")
(command "_circle" "5116.424,896.7" "0.15")
(command "_circle" "5116.049,896.7" "0.15")
(command "_circle" "5117.924,898.7" "0.075")
(command "_circle" "5117.549,898.7" "0.15")
(command "_circle" "5117.174,898.7" "0.15")
(command "_circle" "5116.799,898.7" "0.15")
(command "_circle" "5116.424,898.7" "0.15")
(command "_circle" "5116.049,898.7" "0.15")
(command "_circle" "5117.924,900.7" "0.075")
(command "_circle" "5117.549,900.7" "0.075")
(command "_circle" "5117.174,900.7" "0.075")
(command "_circle" "5116.799,900.7" "0.075")
(command "_circle" "5116.424,900.7" "0.075")
(command "_circle" "5116.049,900.7" "0.075")
(command "_circle" "5115.674,900.7" "0.15")
(command "_circle" "5117.924,902.7" "0.075")
(command "_circle" "5117.549,902.7" "0.15")
(command "_circle" "5117.174,902.7" "0.075")
(command "_circle" "5116.799,902.7" "0.075")
(command "_circle" "5116.424,902.7" "0.075")
(command "_circle" "5116.049,902.7" "0.075")
(command "_circle" "5115.674,902.7" "0.15")
(command "_circle" "5117.924,904.7" "0.075")
(command "_circle" "5117.549,904.7" "0.075")
(command "_circle" "5117.174,904.7" "0.15")
(command "_circle" "5116.799,904.7" "0.075")
(command "_circle" "5116.424,904.7" "0.075")
(command "_circle" "5116.049,904.7" "0.075")
(command "_circle" "5115.674,904.7" "0.15")
(command "_circle" "5117.924,906.7" "0.075")
(command "_circle" "5117.549,906.7" "0.15")
(command "_circle" "5117.174,906.7" "0.15")
(command "_circle" "5116.799,906.7" "0.075")
(command "_circle" "5116.424,906.7" "0.075")
(command "_circle" "5116.049,906.7" "0.075")
(command "_circle" "5115.674,906.7" "0.15")
(command "_circle" "5117.924,908.7" "0.075")
(command "_circle" "5117.549,908.7" "0.075")
(command "_circle" "5117.174,908.7" "0.075")
(command "_circle" "5116.799,908.7" "0.15")
(command "_circle" "5116.424,908.7" "0.075")
(command "_circle" "5116.049,908.7" "0.075")
(command "_circle" "5115.674,908.7" "0.15")
(command "_circle" "5117.924,910.7" "0.075")
(command "_circle" "5117.549,910.7" "0.15")
(command "_circle" "5117.174,910.7" "0.075")
(command "_circle" "5116.799,910.7" "0.15")
(command "_circle" "5116.424,910.7" "0.075")
(command "_circle" "5116.049,910.7" "0.075")
(command "_circle" "5115.674,910.7" "0.15")
(command "_circle" "5117.924,912.7" "0.075")
(command "_circle" "5117.549,912.7" "0.075")
(command "_circle" "5117.174,912.7" "0.15")
(command "_circle" "5116.799,912.7" "0.15")
(command "_circle" "5116.424,912.7" "0.075")
(command "_circle" "5116.049,912.7" "0.075")
(command "_circle" "5115.674,912.7" "0.15")
(command "_circle" "5117.924,914.7" "0.075")
(command "_circle" "5117.549,914.7" "0.15")
(command "_circle" "5117.174,914.7" "0.15")
(command "_circle" "5116.799,914.7" "0.15")
(command "_circle" "5116.424,914.7" "0.075")
(command "_circle" "5116.049,914.7" "0.075")
(command "_circle" "5115.674,914.7" "0.15")
(command "_circle" "5117.924,916.7" "0.075")
(command "_circle" "5117.549,916.7" "0.075")
(command "_circle" "5117.174,916.7" "0.075")
(command "_circle" "5116.799,916.7" "0.075")
(command "_circle" "5116.424,916.7" "0.15")
(command "_circle" "5116.049,916.7" "0.075")
(command "_circle" "5115.674,916.7" "0.15")
(command "_circle" "5117.924,918.7" "0.075")
(command "_circle" "5117.549,918.7" "0.15")
(command "_circle" "5117.174,918.7" "0.075")
(command "_circle" "5116.799,918.7" "0.075")
(command "_circle" "5116.424,918.7" "0.15")
(command "_circle" "5116.049,918.7" "0.075")
(command "_circle" "5115.674,918.7" "0.15")
(command "_circle" "5117.924,920.7" "0.075")
(command "_circle" "5117.549,920.7" "0.075")
(command "_circle" "5117.174,920.7" "0.15")
(command "_circle" "5116.799,920.7" "0.075")
(command "_circle" "5116.424,920.7" "0.15")
(command "_circle" "5116.049,920.7" "0.075")
(command "_circle" "5115.674,920.7" "0.15")
(command "_circle" "5117.924,922.7" "0.075")
(command "_circle" "5117.549,922.7" "0.15")
(command "_circle" "5117.174,922.7" "0.15")
(command "_circle" "5116.799,922.7" "0.075")
(command "_circle" "5116.424,922.7" "0.15")
(command "_circle" "5116.049,922.7" "0.075")
(command "_circle" "5115.674,922.7" "0.15")
(command "_circle" "5117.924,924.7" "0.075")
(command "_circle" "5117.549,924.7" "0.075")
(command "_circle" "5117.174,924.7" "0.075")
(command "_circle" "5116.799,924.7" "0.15")
(command "_circle" "5116.424,924.7" "0.15")
(command "_circle" "5116.049,924.7" "0.075")
(command "_circle" "5115.674,924.7" "0.15")
(command "_circle" "5117.924,926.7" "0.075")
(command "_circle" "5117.549,926.7" "0.15")
(command "_circle" "5117.174,926.7" "0.075")
(command "_circle" "5116.799,926.7" "0.15")
(command "_circle" "5116.424,926.7" "0.15")
(command "_circle" "5116.049,926.7" "0.075")
(command "_circle" "5115.674,926.7" "0.15")
(command "_circle" "5117.924,928.7" "0.075")
(command "_circle" "5117.549,928.7" "0.075")
(command "_circle" "5117.174,928.7" "0.15")
(command "_circle" "5116.799,928.7" "0.15")
(command "_circle" "5116.424,928.7" "0.15")
(command "_circle" "5116.049,928.7" "0.075")
(command "_circle" "5115.674,928.7" "0.15")
(command "_circle" "5117.924,930.7" "0.075")
(command "_circle" "5117.549,930.7" "0.15")
(command "_circle" "5117.174,930.7" "0.15")
(command "_circle" "5116.799,930.7" "0.15")
(command "_circle" "5116.424,930.7" "0.15")
(command "_circle" "5116.049,930.7" "0.075")
(command "_circle" "5115.674,930.7" "0.15")
(command "_circle" "5117.924,932.7" "0.075")
(command "_circle" "5117.549,932.7" "0.075")
(command "_circle" "5117.174,932.7" "0.075")
(command "_circle" "5116.799,932.7" "0.075")
(command "_circle" "5116.424,932.7" "0.075")
(command "_circle" "5116.049,932.7" "0.15")
(command "_circle" "5115.674,932.7" "0.15")
(command "_circle" "5117.924,934.7" "0.075")
(command "_circle" "5117.549,934.7" "0.15")
(command "_circle" "5117.174,934.7" "0.075")
(command "_circle" "5116.799,934.7" "0.075")
(command "_circle" "5116.424,934.7" "0.075")
(command "_circle" "5116.049,934.7" "0.15")
(command "_circle" "5115.674,934.7" "0.15")
(command "_circle" "5117.924,936.7" "0.075")
(command "_circle" "5117.549,936.7" "0.075")
(command "_circle" "5117.174,936.7" "0.15")
(command "_circle" "5116.799,936.7" "0.075")
(command "_circle" "5116.424,936.7" "0.075")
(command "_circle" "5116.049,936.7" "0.15")
(command "_circle" "5115.674,936.7" "0.15")
(command "_circle" "5117.924,938.7" "0.075")
(command "_circle" "5117.549,938.7" "0.15")
(command "_circle" "5117.174,938.7" "0.15")
(command "_circle" "5116.799,938.7" "0.075")
(command "_circle" "5116.424,938.7" "0.075")
(command "_circle" "5116.049,938.7" "0.15")
(command "_circle" "5115.674,938.7" "0.15")
(command "_circle" "5117.924,940.7" "0.075")
(command "_circle" "5117.549,940.7" "0.075")
(command "_circle" "5117.174,940.7" "0.075")
(command "_circle" "5116.799,940.7" "0.15")
(command "_circle" "5116.424,940.7" "0.075")
(command "_circle" "5116.049,940.7" "0.15")
(command "_circle" "5115.674,940.7" "0.15")
(command "_circle" "5117.924,942.7" "0.075")
(command "_circle" "5117.549,942.7" "0.15")
(command "_circle" "5117.174,942.7" "0.075")
(command "_circle" "5116.799,942.7" "0.15")
(command "_circle" "5116.424,942.7" "0.075")
(command "_circle" "5116.049,942.7" "0.15")
(command "_circle" "5115.674,942.7" "0.15")
(command "_circle" "5117.924,944.7" "0.075")
(command "_circle" "5117.549,944.7" "0.075")
(command "_circle" "5117.174,944.7" "0.15")
(command "_circle" "5116.799,944.7" "0.15")
(command "_circle" "5116.424,944.7" "0.075")
(command "_circle" "5116.049,944.7" "0.15")
(command "_circle" "5115.674,944.7" "0.15")
(command "_circle" "5117.924,946.7" "0.075")
(command "_circle" "5117.549,946.7" "0.15")
(command "_circle" "5117.174,946.7" "0.15")
(command "_circle" "5116.799,946.7" "0.15")
(command "_circle" "5116.424,946.7" "0.075")
(command "_circle" "5116.049,946.7" "0.15")
(command "_circle" "5115.674,946.7" "0.15")
(command "_circle" "5117.924,948.7" "0.075")
(command "_circle" "5117.549,948.7" "0.075")
(command "_circle" "5117.174,948.7" "0.075")
(command "_circle" "5116.799,948.7" "0.075")
(command "_circle" "5116.424,948.7" "0.15")
(command "_circle" "5116.049,948.7" "0.15")
(command "_circle" "5115.674,948.7" "0.15")
(command "_circle" "5117.924,950.7" "0.075")
(command "_circle" "5117.549,950.7" "0.15")
(command "_circle" "5117.174,950.7" "0.075")
(command "_circle" "5116.799,950.7" "0.075")
(command "_circle" "5116.424,950.7" "0.15")
(command "_circle" "5116.049,950.7" "0.15")
(command "_circle" "5115.674,950.7" "0.15")
(command "_circle" "5117.924,952.7" "0.075")
(command "_circle" "5117.549,952.7" "0.075")
(command "_circle" "5117.174,952.7" "0.15")
(command "_circle" "5116.799,952.7" "0.075")
(command "_circle" "5116.424,952.7" "0.15")
(command "_circle" "5116.049,952.7" "0.15")
(command "_circle" "5115.674,952.7" "0.15")
(command "_circle" "5117.924,954.7" "0.075")
(command "_circle" "5117.549,954.7" "0.15")
(command "_circle" "5117.174,954.7" "0.15")
(command "_circle" "5116.799,954.7" "0.075")
(command "_circle" "5116.424,954.7" "0.15")
(command "_circle" "5116.049,954.7" "0.15")
(command "_circle" "5115.674,954.7" "0.15")
(command "_circle" "5117.924,956.7" "0.075")
(command "_circle" "5117.549,956.7" "0.075")
(command "_circle" "5117.174,956.7" "0.075")
(command "_circle" "5116.799,956.7" "0.15")
(command "_circle" "5116.424,956.7" "0.15")
(command "_circle" "5116.049,956.7" "0.15")
(command "_circle" "5115.674,956.7" "0.15")
(command "_circle" "5117.924,958.7" "0.075")
(command "_circle" "5117.549,958.7" "0.15")
(command "_circle" "5117.174,958.7" "0.075")
(command "_circle" "5116.799,958.7" "0.15")
(command "_circle" "5116.424,958.7" "0.15")
(command "_circle" "5116.049,958.7" "0.15")
(command "_circle" "5115.674,958.7" "0.15")
(command "_circle" "5117.924,960.7" "0.075")
(command "_circle" "5117.549,960.7" "0.075")
(command "_circle" "5117.174,960.7" "0.15")
(command "_circle" "5116.799,960.7" "0.15")
(command "_circle" "5116.424,960.7" "0.15")
(command "_circle" "5116.049,960.7" "0.15")
(command "_circle" "5115.674,960.7" "0.15")
(command "_circle" "5117.924,962.7" "0.075")
(command "_circle" "5117.549,962.7" "0.15")
(command "_circle" "5117.174,962.7" "0.15")
(command "_circle" "5116.799,962.7" "0.15")
(command "_circle" "5116.424,962.7" "0.15")
(command "_circle" "5116.049,962.7" "0.15")
(command "_circle" "5115.674,962.7" "0.15")
(command "_layer" "set" "nitride" "")
(command "_layer" "set" "text" "")
(command-s "_text" "5106.874,963.3" "2" "-90" "a = 370 nm" )
(sssetfirst nil (ssget "_L"))
(if (not (numberp (vl-string-search "Mac" (getvar "platform")))) (c:txtexp))
(command "_layer" "set" "nitride" "")
(command "_layer" "set" "text" "")
(command-s "_text" "5103.874,963.3" "2" "-90" "gap = 270 nm" )
(sssetfirst nil (ssget "_L"))
(if (not (numberp (vl-string-search "Mac" (getvar "platform")))) (c:txtexp))
(command "_layer" "set" "nitride" "")
(command "_layer" "set" "text" "")
(command-s "_text" "5100.874,963.3" "2" "-90" "amplitude = 137 nm" )
(sssetfirst nil (ssget "_L"))
(if (not (numberp (vl-string-search "Mac" (getvar "platform")))) (c:txtexp))
(command "_layer" "set" "nitride" "")
(command "_layer" "set" "text" "")
(command-s "_text" "5097.874,963.3" "2" "-90" "start width = 280 nm" )
(sssetfirst nil (ssget "_L"))
(if (not (numberp (vl-string-search "Mac" (getvar "platform")))) (c:txtexp))
(command "_layer" "set" "nitride" "")
(command "_layer" "set" "text" "")
(command-s "_text" "5094.874,963.3" "2" "-90" "width = 291 nm" )
(sssetfirst nil (ssget "_L"))
(if (not (numberp (vl-string-search "Mac" (getvar "platform")))) (c:txtexp))
(command "_layer" "set" "nitride" "")
(command "_layer" "set" "text" "")
(command-s "_text" "5091.874,963.3" "2" "-90" "taper: 15" )
(sssetfirst nil (ssget "_L"))
(if (not (numberp (vl-string-search "Mac" (getvar "platform")))) (c:txtexp))
(command "_layer" "set" "nitride" "")
(command "_layer" "set" "text" "")
(command-s "_text" "5088.874,963.3" "2" "-90" "nominal: 150" )
(sssetfirst nil (ssget "_L"))
(if (not (numberp (vl-string-search "Mac" (getvar "platform")))) (c:txtexp))
(command "_layer" "set" "nitride" "")
(command "_layer" "set" "indicators" "")
(setq coords (list 
(list 5040.415 940) 
(list 5040.415 920) 
(list 5020.415 900) 
(list 5040.415 880) 
(list 5040.415 860) 
(list 5040.415 900) 
(list 5040.415 887.0711) 
(list 5027.4861 900) 
(list 5040.415 912.9289) 
(list 5040.415 900)))
(apply 'command (append '("pline") coords '("c")))
(command "._fillet" "radius" "1" "._fillet" "P" (entlast))
(setq coords (list 
(list 5199.585 940) 
(list 5199.585 920) 
(list 5219.585 900) 
(list 5199.585 880) 
(list 5199.585 860) 
(list 5199.585 900) 
(list 5199.585 887.0711) 
(list 5212.5139 900) 
(list 5199.585 912.9289) 
(list 5199.585 900)))
(apply 'command (append '("pline") coords '("c")))
(command "._fillet" "radius" "1" "._fillet" "P" (entlast))
(command "_layer" "set" "holes" "")
(command "_circle" "5038.0629,914.1124" "0.5")
(command "_circle" "5035.7109,911.7603" "0.5")
(command "_circle" "5033.3588,909.4083" "0.5")
(command "_circle" "5031.0067,907.0562" "0.5")
(command "_circle" "5028.6547,904.7041" "0.5")
(command "_circle" "5026.3026,902.3521" "0.5")
(command "_circle" "5023.9505,900" "0.5")
(command "_circle" "5026.3026,897.6479" "0.5")
(command "_circle" "5028.6547,895.2959" "0.5")
(command "_circle" "5031.0067,892.9438" "0.5")
(command "_circle" "5033.3588,890.5917" "0.5")
(command "_circle" "5035.7109,888.2397" "0.5")
(command "_circle" "5038.0629,885.8876" "0.5")
(command "_circle" "5201.9371,914.1124" "0.5")
(command "_circle" "5204.2891,911.7603" "0.5")
(command "_circle" "5206.6412,909.4083" "0.5")
(command "_circle" "5208.9933,907.0562" "0.5")
(command "_circle" "5211.3453,904.7041" "0.5")
(command "_circle" "5213.6974,902.3521" "0.5")
(command "_circle" "5216.0495,900" "0.5")
(command "_circle" "5213.6974,897.6479" "0.5")
(command "_circle" "5211.3453,895.2959" "0.5")
(command "_circle" "5208.9933,892.9438" "0.5")
(command "_circle" "5206.6412,890.5917" "0.5")
(command "_circle" "5204.2891,888.2397" "0.5")
(command "_circle" "5201.9371,885.8876" "0.5")
(command "_layer" "set" "nitride" "")
(command "_block" "blkcoupler16" "5120,900" coupler16 "")
(command "_insert" "blkcoupler16" "5120,900" "1" "1" "0")
(command "_insert" "blkcoupler16" "5120,900" "1" "1" "180")
(command "_block" "blksinglenanobeam16" "5120,900" singlenanobeam16 "")
(command "_insert" "blksinglenanobeam16" "5120,900" "1" "1" "0")
(command "_insert" "blksinglenanobeam16" "5120,900" "1" "1" "180")
(command "_block" "blkanglednodearray16" "5120,900" anglednodearray16 "")
(command "_insert" "blkanglednodearray16" "5120,900" "1" "1" "0")
(command "_insert" "blkanglednodearray16" "5120,900" "1" "1" "180")
(command "_block" "blkcooledsinglenanobeam16" "5120,900" cooledsinglenanobeam16 "")
(command "_insert" "blkcooledsinglenanobeam16" "5120,900" "1" "1" "0")
(command "_insert" "blkcooledsinglenanobeam16" "5120,900" "1" "1" "180")
(command "_block" "blkyjunction16" "5120,900" yjunction16 "")
(command "_insert" "blkyjunction16" "5120,900" "1" "1" "0")
(command "_insert" "blkyjunction16" "5120,900" "1" "1" "180")
; DRAWING BULGING VEE GROOVE
(command "_layer" "set" "vgroove" "")
(setq coords (list 
(list 5045.415 -605) 
(list 5045.415 0) 
(list 5045.415 0) 
(list 5045.415 1800) 
(list 5045.415 1800) 
(list 5045.415 2405) 
(list 5194.585 2405) 
(list 5194.585 1800) 
(list 5194.585 1800) 
(list 5194.585 0) 
(list 5194.585 0) 
(list 5194.585 -605)))
(apply 'command (append '("pline") coords '("c")))
(command "._fillet" "radius" "0" "._fillet" "P" (entlast))
(command "_layer" "set" "window" "")
(command "_rectangle" "5045.415,-1935" "5194.585,-600")
(command "_rectangle" "5045.415,2400" "5194.585,5300")
(command "_layer" "set" "grid" "")
(command "_rectangle" "5046.415,-1934" "5069.9433,-1909.2133")
(command "_array" "last" "" "R" "75" "3" "25.7867" "24.5283")
(command "_rectangle" "5121,-1934" "5144.5283,-1909.2133")
(command "_array" "last" "" "R" "75" "3" "25.7867" "24.5283")
(command "_rectangle" "5046.415,1" "5069.9433,25.7")
(command "_array" "last" "" "R" "70" "3" "25.7" "24.5283")
(command "_rectangle" "5121,1" "5144.5283,25.7")
(command "_array" "last" "" "R" "70" "3" "25.7" "24.5283")
(command "_rectangle" "5046.415,1801" "5069.9433,1825.9185")
(command "_array" "last" "" "R" "135" "3" "25.9185" "24.5283")
(command "_rectangle" "5121,1801" "5144.5283,1825.9185")
(command "_array" "last" "" "R" "135" "3" "25.9185" "24.5283")
(command "_layer" "set" "vgrooveFDA" "")
(command "_rectangle" "5194.585,-2233" "5045.415,-1933")
(command "_layer" "set" "nitride" "")
(command "_layer" "set" "holes" "")
(command "_circle" "5197.085,331.5" "0.5")
(command "_array" "last" "" "R" "379" "1" "3" "2.5")
(command "_circle" "5042.915,331.5" "0.5")
(command "_array" "last" "" "R" "379" "1" "3" "-2.5")
(command "_layer" "set" "nitride" "")
(command "_layer" "set" "window" "")
(command "_layer" "set" "window" "")
(command "_rectangle" "5199.585,0" "6426.225,1800")
(command "._fillet" "radius" "20" "._fillet" "P" (entlast))
(command "_layer" "set" "grid" "")
(command "_rectangle" "5200.585,1" "5225.1192,25.7")
(command "_array" "last" "" "R" "70" "48" "25.7" "25.5342")
; DRAWING REGION LAYER
(command "_layer" "set" "regionLayer16" "")
(command "_rectangle" "5040,-460" "5200,2260")
(command "_layer" "set" "nitride" "")
(setq coupler16 nil)
(setq singlenanobeam16 nil)
(setq anglednodearray16 nil)
(setq cooledsinglenanobeam16 nil)
(setq yjunction16 nil)
(command "_layer" "set" "extent" "")
(command "_rectangle" "-2040,-2480" "-2020,-2460")
(command "_rectangle" "7940,-2480" "7960,-2460")
(command "_rectangle" "-2040,8500" "-2020,8520")
(command "_rectangle" "7940,8500" "7960,8520")
(command "_layer" "set" "marks" "")
(setq coords (list 
(list 0 -880) 
(list 90 -880) 
(list 90 -810) 
(list 70 -810) 
(list 70 -790) 
(list 90 -790) 
(list 90 -880) 
(list 160 -880) 
(list 160 -720) 
(list 0 -720)))
(apply 'command (append '("pline") coords '("c")))
(setq coords (list 
(list 5760 -880) 
(list 5850 -880) 
(list 5850 -810) 
(list 5830 -810) 
(list 5830 -790) 
(list 5850 -790) 
(list 5850 -880) 
(list 5920 -880) 
(list 5920 -720) 
(list 5760 -720)))
(apply 'command (append '("pline") coords '("c")))
(setq coords (list 
(list 0 2640) 
(list 90 2640) 
(list 90 2710) 
(list 70 2710) 
(list 70 2730) 
(list 90 2730) 
(list 90 2640) 
(list 160 2640) 
(list 160 2800) 
(list 0 2800)))
(apply 'command (append '("pline") coords '("c")))
(setq coords (list 
(list 5760 2640) 
(list 5850 2640) 
(list 5850 2710) 
(list 5830 2710) 
(list 5830 2730) 
(list 5850 2730) 
(list 5850 2640) 
(list 5920 2640) 
(list 5920 2800) 
(list 5760 2800)))
(apply 'command (append '("pline") coords '("c")))
(command "_layer" "set" "marks" "")
(command "_rectangle" "70,-330" "90,-310")
(command "_rectangle" "5830,-330" "5850,-310")
(command "_rectangle" "70,2230" "90,2250")
(command "_rectangle" "5830,2230" "5850,2250")
(command "_layer" "set" "nitride" "")
(command "_zoom" "extents")
; DRAW LAYERS, SET COLORS
(command "_layer" "OFF" "grid" "")
(command "_saveas" "DXF" "Version" "2000" "" "/Users/Andrew/Documents/Repositories/fabrication/Writes/2016-05-26 Rugrats/lil16.dxf")
